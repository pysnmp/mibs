PERLE-IOLAN-SDS-MIB DEFINITIONS ::= BEGIN

  -- The private MIB module for the Perle IOLAN SDS, SCS and STS
  -- version 17.01.17 (year.month.day)
  

  IMPORTS
        MODULE-IDENTITY, NOTIFICATION-TYPE, OBJECT-TYPE, 
        IpAddress, Counter32, Unsigned32, Integer32, enterprises
                FROM SNMPv2-SMI
        TEXTUAL-CONVENTION, DisplayString, MacAddress
                FROM SNMPv2-TC
        MODULE-COMPLIANCE, OBJECT-GROUP, NOTIFICATION-GROUP
                FROM SNMPv2-CONF;
 
 
  sdsMIB         MODULE-IDENTITY
    LAST-UPDATED "201701170000Z"
    ORGANIZATION "Perle Systems Limited"
    CONTACT-INFO 
            "Postal: Perle Systems Limited 
                     60 Renfrew Drive 
                     Markham, Ontario 
                     Canada 
                     L3R 0E1 
 
             http://www.perle.com/"
    DESCRIPTION
            "The private MIB module for the Perle IOLAN SDS, SCS and STS"
    REVISION    "201701170000Z"
        DESCRIPTION
             "Updated for 4.9G firmware release (sds-l)"
    REVISION    "201603310000Z"
        DESCRIPTION
             "Updated for 4.8G firmware release"    
    REVISION    "201512080000Z"
        DESCRIPTION
             "Updated for 4.7G firmware release (sds-w)"
    REVISION    "201410210000Z"
        DESCRIPTION
             "Updated for 4.6G firmware release"
    REVISION    "201306250000Z"
        DESCRIPTION
             "Updated for 4.5G firmware release"
    REVISION    "201205140000Z"
        DESCRIPTION
             "Updated for 4.4G firmware release"
    REVISION    "201201070000Z"
        DESCRIPTION
             "Updated again for 4.3G firmware release"
    REVISION    "201103080000Z"
        DESCRIPTION
             "Updated for 4.3G firmware release"
    REVISION    "201010290000Z"
        DESCRIPTION
             "Updated for 4.2G firmware release"
    REVISION    "200909140000Z"
        DESCRIPTION
             "Resolved issues with nested tables and several MIB syntax errors.
              MIB no longer compatible with firmware versions prior to 4.1"
    REVISION    "200810200000Z"
        DESCRIPTION
             "Updated for 3.6G firmware release"
    REVISION    "200806250000Z"
        DESCRIPTION
             "Updated for 3.5G firmware release"
    REVISION    "200711300000Z"
        DESCRIPTION
             "Updated for 3.4G firmware release"
    REVISION    "200707240000Z"
        DESCRIPTION
             "Updated for 3.2G firmware release"
    REVISION    "200610240000Z"
        DESCRIPTION
             "Updated for 3.0G firmware release"
    REVISION    "200606210000Z"
        DESCRIPTION
             "Updated for 2.4G firmware release"
    REVISION    "200604230000Z"
        DESCRIPTION
             "Updated for 2.3G firmware release"
    REVISION    "200603170000Z"
        DESCRIPTION
             "Updated for 2.1G firmware release"
    REVISION    "200601090000Z"
        DESCRIPTION
             "Updated descriptions"
    REVISION    "200511100000Z"
        DESCRIPTION
             "Added support for: multiple Ethernet interfaces,
              1000 Mbps Ethernet, software serial port termination,
              and dedicated serial console port"
    REVISION    "200511090000Z"
        DESCRIPTION
             "Added support for single character interrupt feature.  Fixed
              syntactical errors and updated descriptions."             
    REVISION    "200506100000Z"
        DESCRIPTION
             "Added support for DCE serial interface and 2-port model"
    REVISION    "200506010000Z"
        DESCRIPTION
             "Added support for 28800 baud"
    REVISION    "200505040000Z"
        DESCRIPTION
             "Added SSL Configuration support"
    REVISION    "200501140000Z"
        DESCRIPTION
             "Initial Release"

--  ::= { enterprises 1966 10 }        this OID is obsolete
    ::= { enterprises 1966 12 }
 
  perle          OBJECT IDENTIFIER  ::= { enterprises 1966 }


sdsMIBObjects OBJECT IDENTIFIER
        ::= { sdsMIB 1 }

sdsMIBNotifications OBJECT IDENTIFIER
        ::= { sdsMIB 2 }

sdsMIBConformance OBJECT IDENTIFIER
        ::= { sdsMIB 3 }

  adminInfo            OBJECT IDENTIFIER  ::= { sdsMIBObjects 1 }

  serverInfo           OBJECT IDENTIFIER  ::= { sdsMIBObjects 2 }

  hostsInfo            OBJECT IDENTIFIER  ::= { sdsMIBObjects 3 }

  userInfo             OBJECT IDENTIFIER  ::= { sdsMIBObjects 4 }

  portInfo             OBJECT IDENTIFIER  ::= { sdsMIBObjects 5 }

  modemInfo            OBJECT IDENTIFIER  ::= { sdsMIBObjects 6 }

  servicesInfo         OBJECT IDENTIFIER  ::= { sdsMIBObjects 7 }

  trueportInfo  OBJECT IDENTIFIER  ::= { sdsMIBObjects 8 }

  radiusInfo           OBJECT IDENTIFIER  ::= { sdsMIBObjects 9 }

  kerberosInfo         OBJECT IDENTIFIER  ::= { sdsMIBObjects 10 }

  ldapInfo             OBJECT IDENTIFIER  ::= { sdsMIBObjects 11 }

  tacacsInfo           OBJECT IDENTIFIER  ::= { sdsMIBObjects 12 }

  securidInfo          OBJECT IDENTIFIER  ::= { sdsMIBObjects 13 }

  nisInfo              OBJECT IDENTIFIER  ::= { sdsMIBObjects 14 }

  sshServerInfo        OBJECT IDENTIFIER  ::= { sdsMIBObjects 15 }

  defUserInfo          OBJECT IDENTIFIER  ::= { sdsMIBObjects 16 }

  snmpInfo             OBJECT IDENTIFIER  ::= { sdsMIBObjects 17 }

  dnsInfo              OBJECT IDENTIFIER  ::= { sdsMIBObjects 18 }

  winsInfo             OBJECT IDENTIFIER  ::= { sdsMIBObjects 19 }

  gatewayInfo          OBJECT IDENTIFIER  ::= { sdsMIBObjects 20 }

  syslogInfo           OBJECT IDENTIFIER  ::= { sdsMIBObjects 21 }

  emailInfo            OBJECT IDENTIFIER  ::= { sdsMIBObjects 22 }

  ripInfo              OBJECT IDENTIFIER  ::= { sdsMIBObjects 23 }

  timeInfo             OBJECT IDENTIFIER  ::= { sdsMIBObjects 24 }

  fileInfo             OBJECT IDENTIFIER  ::= { sdsMIBObjects 25 }

  -- OBJECT IDENTIFIER  ::= { sdsMIBObjects 26 }  is obsolete

  sntpStatsInfo        OBJECT IDENTIFIER  ::= { sdsMIBObjects 27 }

  ripTableInfo         OBJECT IDENTIFIER  ::= { sdsMIBObjects 28 }

  tcpConnStatsInfo     OBJECT IDENTIFIER  ::= { sdsMIBObjects 29 }

  udpConnStatsInfo     OBJECT IDENTIFIER  ::= { sdsMIBObjects 30 }

  ipv6StatsInfo        OBJECT IDENTIFIER  ::= { sdsMIBObjects 31 }

  icmpv6StatsInfo      OBJECT IDENTIFIER  ::= { sdsMIBObjects 32 }

  udpv6StatsInfo       OBJECT IDENTIFIER  ::= { sdsMIBObjects 33 }

  tcpConnv6StatsInfo   OBJECT IDENTIFIER  ::= { sdsMIBObjects 34 }

  udpConnv6StatsInfo   OBJECT IDENTIFIER  ::= { sdsMIBObjects 35 }

  routev6Info          OBJECT IDENTIFIER  ::= { sdsMIBObjects 36 }

  ripv6TableInfo       OBJECT IDENTIFIER  ::= { sdsMIBObjects 37 }

  interfacev6Info      OBJECT IDENTIFIER  ::= { sdsMIBObjects 38 }

  sslInfo              OBJECT IDENTIFIER  ::= { sdsMIBObjects 39 }

  consoleInfo          OBJECT IDENTIFIER  ::= { sdsMIBObjects 40 }
  
  ethStatsInfo         OBJECT IDENTIFIER  ::= { sdsMIBObjects 41 }
  
  modbusGatewayInfo    OBJECT IDENTIFIER  ::= { sdsMIBObjects 42 }
  
  modbusStatsInfo      OBJECT IDENTIFIER  ::= { sdsMIBObjects 43 }
  
  customAppServerInfo  OBJECT IDENTIFIER  ::= { sdsMIBObjects 44 }

  ioInfo               OBJECT IDENTIFIER ::=  { sdsMIBObjects 45 }

  clusteringInfo       OBJECT IDENTIFIER  ::= { sdsMIBObjects 46 }
  
  dynamicDNSInfo       OBJECT IDENTIFIER  ::= { sdsMIBObjects 47 }

  pciInfo              OBJECT IDENTIFIER  ::= { sdsMIBObjects 48 }

  vmodemPhoneInfo      OBJECT IDENTIFIER  ::= { sdsMIBObjects 49 }

  ipsecInfo            OBJECT IDENTIFIER  ::= { sdsMIBObjects 50 }

  ipv6Info             OBJECT IDENTIFIER  ::= { sdsMIBObjects 51 }

  l2tpInfo             OBJECT IDENTIFIER  ::= { sdsMIBObjects 52 }
  
  vpnexceptionInfo     OBJECT IDENTIFIER  ::= { sdsMIBObjects 53 }

  httpTunInfo          OBJECT IDENTIFIER ::=  { sdsMIBObjects 54 }

  sftpInfo             OBJECT IDENTIFIER ::=  { sdsMIBObjects 55 }

  wlanInfo             OBJECT IDENTIFIER ::=  { sdsMIBObjects 56 }
  
  wwanInfo             OBJECT IDENTIFIER ::=  { sdsMIBObjects 57 }

  sfpInfo       	   OBJECT IDENTIFIER ::=  { sdsMIBObjects 58 }

  frontPanelInfo       OBJECT IDENTIFIER ::=  { sdsMIBObjects 59 }

  -- Data Types

  YesNoValue ::= TEXTUAL-CONVENTION
      STATUS        current
      DESCRIPTION
              "Represents a YES or NO value."
      SYNTAX        INTEGER { no(1), yes(2) }

  OnOffValue ::= TEXTUAL-CONVENTION
      STATUS        current
      DESCRIPTION
              "Represents an ON or OFF value."
      SYNTAX        INTEGER { off(1), on(2) }

  Hex8 ::= TEXTUAL-CONVENTION
      DISPLAY-HINT  "1x"
      STATUS        current
      DESCRIPTION
              "Represents a one byte octet hex value."
      SYNTAX        OCTET STRING (SIZE(1))

  Hex32 ::= TEXTUAL-CONVENTION
      DISPLAY-HINT  "4x"
      STATUS        current
      DESCRIPTION
              "Represents a four octet hex value."
      SYNTAX        OCTET STRING (SIZE(4))

  TrueportBaud ::= TEXTUAL-CONVENTION
      STATUS        current
      DESCRIPTION
              "Represents TruePort baudrate mapping."
      SYNTAX      INTEGER {
          b50(1),
          b75(2),
          b110(3),
          b134(4),
          b150(5),
          b200(6),
          b300(7),
          b600(8),
          b1200(9),
          b1800(10),
          b2400(11),
          b4800(12),
          b9600(13),
          b19200(14),
          b38400(15),
          b57600(16),
          b115200(17),
          b230400(18),
          b28800(23),
          bCustom(24)
      }

  Date ::= TEXTUAL-CONVENTION
      STATUS       current
      DESCRIPTION
            "A date specification. In the format dd/mm/yyyy

            field   contents                  range
            -----   --------                  -----
              1       day                       1..31
              2       month                     1..12
              3       year*                     0..65536
            "
      SYNTAX       OCTET STRING (SIZE (8..10))

  Time ::= TEXTUAL-CONVENTION
      STATUS       current
      DESCRIPTION
            "A time specification. In the format hh:mm:ss

            field  contents                  range
            -----  --------                  -----
              1    hour                      0..23
              2    minutes                   0..59
              3    seconds                   0..59
            "
      SYNTAX       OCTET STRING (SIZE (5..8))

  Ipv4v6Address ::= TEXTUAL-CONVENTION
      DISPLAY-HINT "255a"
      STATUS       current
      DESCRIPTION
          "An IPv4 or IPv6 address"
      SYNTAX  OCTET STRING (SIZE (0..255))

  Ipv6InterfaceId ::= TEXTUAL-CONVENTION
      DISPLAY-HINT "255a"
      STATUS       current
      DESCRIPTION
          "An IPv6 Interface Identifier. The first 64 bits must be 0"
      SYNTAX OCTET STRING (SIZE (0..255))

  GenericTableIndex ::= TEXTUAL-CONVENTION
    DISPLAY-HINT      "d"
    STATUS            current
    DESCRIPTION
            "An arbitrary value that uniquely identifies the entity. The value 
             should be a small, positive integer. Index values for different 
             entities are not necessarily contiguous."
    SYNTAX Integer32 (1..2147483647)

  PortNumber ::= TEXTUAL-CONVENTION
    DISPLAY-HINT      "d"
    STATUS            current
    DESCRIPTION
            "Serial Port/Line number. Valid values are 1 to maximum port number the 
             Device Server supports"
    SYNTAX Integer32 (1..49)
    
  ContainerStatus ::= TEXTUAL-CONVENTION
     STATUS        current
     DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
     SYNTAX      INTEGER {
          active(1),
          modified(2),
          applyChanges(4),
          discardChanges(6)
          }
      
  
  --  adminInfo group.

  adminFunction OBJECT-TYPE
      SYNTAX INTEGER {
        writeToFlash(1),
        resetToFactoryDefaults(2),
        reboot(3),
        resetSecurIDNodeSecret(4)
      }
      MAX-ACCESS read-write
      STATUS current
      DESCRIPTION
            "Perform a specific function on the Device Server.
             If you want to save all the changes that have been
             submitted to the Device Server, you need to expand
             the adminInfo container folder and SET the adminFunction
             to 1 to write to FLASH. To make the configuration
             changes take effect, SET the adminFunction to 3 to
             reboot the Device Server."
      ::= {adminInfo 1 }

  adminLastFunction OBJECT-TYPE
      SYNTAX INTEGER {
        writeToFlash(1),
        resetToFactoryDefaults(2),
        reboot(3),
        resetSecurIDNodeSecret(4)
      }
      MAX-ACCESS read-only
      STATUS current
      DESCRIPTION
            "The last function requested"
      ::= {adminInfo 2 }

  adminStatus OBJECT-TYPE
      SYNTAX INTEGER {
        successful(1),
        error(2),
        inProgress(3)
      }
      MAX-ACCESS read-only
      STATUS current
      DESCRIPTION
            "The status of the last function performed."
      ::= {adminInfo 3 }

  adminSystemDate OBJECT-TYPE
      SYNTAX      Date
      MAX-ACCESS  read-write
      STATUS      current
      DESCRIPTION
              "The system date.
               Format dd/mm/yyyy"
      ::= { adminInfo 4 }

  adminSystemTime OBJECT-TYPE
      SYNTAX      Time
      MAX-ACCESS  read-write
      STATUS      current
      DESCRIPTION
              "The system time (local time).
               Format hh:mm:ss"
      ::= { adminInfo 5 }

  adminKillLine OBJECT-TYPE
      SYNTAX      PortNumber
      MAX-ACCESS  read-write
      STATUS      current
      DESCRIPTION
            "Enter the line number you want to reset"
      ::= { adminInfo 6 }
      
   adminGetClusteredSlavePortNames OBJECT-TYPE
      SYNTAX      IpAddress
      MAX-ACCESS  read-write
      STATUS      current
      DESCRIPTION
              "Set the clustered slave IP address in order to retrieve its
               serial port names."
      ::= { adminInfo 7}            

   adminPowerOn OBJECT-TYPE
      SYNTAX      DisplayString(SIZE(1..5))
      MAX-ACCESS  read-write
      STATUS      current
      DESCRIPTION
              "Turn on the power of the whole line(if the line is not a power
               management line) or a plug (the line is a power management line),
               and the input format is line#:plug#(1 based)."
      ::= { adminInfo 8}            

   adminPowerOff OBJECT-TYPE
      SYNTAX      DisplayString(SIZE(1..5))
      MAX-ACCESS  read-write
      STATUS      current
      DESCRIPTION
              "Turn off the power of the whole line(if the line is not a power
               management line) or a plug (the line is a power management line),
               and the input format is line#:plug#(1 based)."
      ::= { adminInfo 9}            
      
   adminPowerBoot OBJECT-TYPE
      SYNTAX      DisplayString(SIZE(1..5))
      MAX-ACCESS  read-write
      STATUS      current
      DESCRIPTION
              "Boot the whole line(if the line is not a power management line) or
               a plug (the line is a power management line), and the input format 
               is line#:plug#(1 based)."
      ::= { adminInfo 10}            
      
   adminPowerReset OBJECT-TYPE
      SYNTAX      PortNumber
      MAX-ACCESS  read-write
      STATUS      current
      DESCRIPTION
              "Reset whole line(only if the line is a power management line),
               and the input is the line number(1 based)."
      ::= { adminInfo 11}            
      
   adminPowerStatus OBJECT-TYPE
      SYNTAX      DisplayString(SIZE(1..10))
      MAX-ACCESS  read-write
      STATUS      current
      DESCRIPTION
              "Return the status of a plug (the line is a power management line).
               
               The input format is line#:plug#(1 based).  
               The output is one of following strings: 'off', 'on' or 'undefined'."
      ::= { adminInfo 12}

   adminIpsec OBJECT-TYPE
      SYNTAX INTEGER {
        start(1),
        stop(2),
        restart(3)
      }
      MAX-ACCESS read-write
      STATUS current
      DESCRIPTION
            "IPsec functions."
      ::= {adminInfo 13 }    
      
   adminPowerMonitorOn OBJECT-TYPE
      SYNTAX      DisplayString(SIZE(1..5))
      MAX-ACCESS  read-write
      STATUS      current
      DESCRIPTION
              "Enable host monitoring for a power plug, on a serial port 
               configured for power management.
               
               The input format is line#:plug#.
               e.g. Use '5:10' for serial port 5, plug 10."
      ::= { adminInfo 14}            

   adminPowerMonitorOff OBJECT-TYPE
      SYNTAX      DisplayString(SIZE(1..5))
      MAX-ACCESS  read-write
      STATUS      current
      DESCRIPTION
              "Disable host monitoring for a power plug, on a serial port 
               configured for power management.
               
               The input format is line#:plug#.
               e.g. Use '5:10' for serial port 5, plug 10."
      ::= { adminInfo 15 }            
      
   adminPowerMonitorStatus OBJECT-TYPE
      SYNTAX      DisplayString(SIZE(1..10))
      MAX-ACCESS  read-write
      STATUS      current
      DESCRIPTION
              "Return the status of the host monitoring feature for a power plug,
               on a serial port configured for power management.
               
               The input format is line#:plug#.  
               The output is one of following strings: 'off', 'on' or 'undefined'."
      ::= { adminInfo 16 }

   adminPowerMonitorNumberOfReboots OBJECT-TYPE
      SYNTAX      DisplayString(SIZE(1..10))
      MAX-ACCESS  read-write
      STATUS      current
      DESCRIPTION
              "Return the number of power cycles (reboots) initiated by the host 
               monitoring feature for a power plug, on a serial port configured 
               for power management. 
               
               The input format is line#:plug#.  
               The output is a string containing the number of reboots."
      ::= { adminInfo 17 }

   adminPowerMonitorLastRebootTime OBJECT-TYPE
      SYNTAX      DisplayString(SIZE(0..80))
      MAX-ACCESS  read-write
      STATUS      current
      DESCRIPTION
              "Returns the time of the last power cycle (reboot), initiated by the host 
               monitoring feature for a power plug, on a serial port configured for power
               management.
               
               The input format is line#:plug#.  
               The output is a string containing the date and time of the last reboot."
      ::= { adminInfo 18 }
  
   adminPowerMonitorResetRebootInfo OBJECT-TYPE
      SYNTAX      DisplayString(SIZE(1..5))
      MAX-ACCESS  read-write
      STATUS      current
      DESCRIPTION
              "Reset the monitor reboot information (number of reboots and time of 
               last reboot.
               
               The input format is line#:plug#.
               e.g. Use '5:10' for serial port 5, plug 10."
      ::= { adminInfo 19}            

  

  adminResetSerialStatistics OBJECT-TYPE
      SYNTAX      PortNumber
      MAX-ACCESS  read-write
      STATUS      current
      DESCRIPTION
            "Enter the line number you want to reset statistics"
      ::= { adminInfo 20 }
      
  adminChassisSerialNumber      OBJECT-TYPE
     SYNTAX     DisplayString(SIZE(0..32))
     MAX-ACCESS    read-only
     STATUS       current
     DESCRIPTION
            "Chassis Serial Number"
     ::= { adminInfo 21} 
     
  adminSlot1SerialNumber      OBJECT-TYPE
     SYNTAX     DisplayString(SIZE(0..32))
     MAX-ACCESS    read-only
     STATUS       current
     DESCRIPTION
            "Slot 1 Serial Number"
     ::= { adminInfo 22}   

  adminSlot2SerialNumber      OBJECT-TYPE
     SYNTAX     DisplayString(SIZE(0..32))
     MAX-ACCESS    read-only
     STATUS       current
     DESCRIPTION
            "Slot 2 Serial Number"
     ::= { adminInfo 23}

  adminSlot3SerialNumber      OBJECT-TYPE
     SYNTAX     DisplayString(SIZE(0..32))
     MAX-ACCESS    read-only
     STATUS       current
     DESCRIPTION
            "Slto 3 Serial Number"
     ::= { adminInfo 24}

  adminLTECardSerialNumber      OBJECT-TYPE
     SYNTAX     DisplayString(SIZE(0..32))
     MAX-ACCESS    read-only
     STATUS       current
     DESCRIPTION
            "LTE CardSerial Number"
     ::= { adminInfo 25}

  adminWIFICardSerialNumber      OBJECT-TYPE
     SYNTAX     DisplayString(SIZE(0..32))
     MAX-ACCESS    read-only
     STATUS       current
     DESCRIPTION
            "WIFI Card Serial Number"
     ::= { adminInfo 26}

  adminPartNumber		OBJECT-TYPE
     SYNTAX DisplayString(SIZE(0..32))
     MAX-ACCESS    read-only
     STATUS         current
     DESCRIPTION
     			"Device part Number"
     	::= { adminInfo 27}

 adminTemperature      OBJECT-TYPE
 	     SYNTAX DisplayString(SIZE(0..32))
     MAX-ACCESS    read-only
     STATUS         current
     DESCRIPTION
     			"IOLAN Internal temperature"
     	::= { adminInfo 28}

  serverStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { serverInfo 1 }

  serverName OBJECT-TYPE
      SYNTAX      DisplayString(SIZE(1..63))
      MAX-ACCESS  read-write
      STATUS      current
      DESCRIPTION
              "The name of the Device Server."
      ::= { serverInfo 2 }

  serverDomainName OBJECT-TYPE
      SYNTAX      DisplayString(SIZE(0..32))
      MAX-ACCESS  read-write
      STATUS      current
      DESCRIPTION
              "The domain name of the Device Server."
      ::= { serverInfo 3 }

  serverIPaddress OBJECT-TYPE
      SYNTAX      IpAddress
      MAX-ACCESS  read-write
      STATUS      current
      DESCRIPTION
              "The Device Server's unique IPv4 network IP address.
               If you are using the Device Server in an IPv6 network,
               this field can be left blank."
      ::= { serverInfo 4 }

  serverSubnetBits OBJECT-TYPE
      SYNTAX      Integer32(0..32)
      MAX-ACCESS  read-write
      STATUS      current
      DESCRIPTION
              "The number of bits in the subnet mask. For example,
               a subnet mask of 255.255.0.0 has 16 subnet/prefix bits.
               Valid values are 0-32. The default is 0. When the value
               is 0, the correct value is determined based on the class
               of the IP Address."
      ::= { serverInfo 5 }

  serverPortBuffering OBJECT-TYPE
      SYNTAX      INTEGER {
               disabled(1),
               local(2),
               remote(3),
               both(4)
      }
      MAX-ACCESS  read-write
      STATUS      current
      DESCRIPTION
              "Specifies where the port buffer log is kept, either Off,
               Local, Remote, or Both. If Remote or Both is selected,
               you must specify an NFS server location for the port buffer log."
      ::= { serverInfo 6 }

  serverViewPortBufferString OBJECT-TYPE
      SYNTAX      DisplayString(SIZE(0..8))
      MAX-ACCESS  read-write
      STATUS      current
      DESCRIPTION
              "The string (up to 8 characters) used by a a session
               connected to a serial port to display the port buffer for
               that particular serial port. You can specify control
               (unprintable) codes by putting the decimal value in angle
               brackets < > (for example, Escape b is <027>b).
               The default is ~view."
      ::= { serverInfo 7 }

  serverTimeStamping OBJECT-TYPE
      SYNTAX      OnOffValue
      MAX-ACCESS  read-write
      STATUS      current
      DESCRIPTION
              "Enable/disable time stamping of the port buffer data."
      ::= { serverInfo 8 }

  serverSessionEscapeString OBJECT-TYPE
      SYNTAX      DisplayString(SIZE(0..8))
      MAX-ACCESS  read-write
      STATUS      current
      DESCRIPTION
              "The key sequence to escape the current session and
              display the session options."
      ::= { serverInfo 9 }

  serverNFSHostName OBJECT-TYPE
      SYNTAX      DisplayString(SIZE(0..14))
      MAX-ACCESS  read-write
      STATUS      current
      DESCRIPTION
              "The NFS host that the Device Server will use for
               its Remote Port Buffering feature. The Device Server
               will open a file on the NFS host for each reverse SSH
               or reverse Telnet line, and send any port data to be
               written to those files. The default is None. This field
               is required when Mode is set to Remote or Both.
               The host name must be defined in the hosts table."
      ::= { serverInfo 10}

  serverNFSDirectory OBJECT-TYPE
      SYNTAX      DisplayString(SIZE(0..40))
      MAX-ACCESS  read-write
      STATUS      current
      DESCRIPTION
              "The directory and/or subdirectories where the Remote Port
               Buffering files will be created. This field is used when
               Port Buffering Mode is set to Remote or Both. For multiple
               Device Servers using the same NFS host, it is recommended
               that each Device Server have its own unique directory to
               house the remote port log files.
               The default is /device_server/portlogs."
      ::= { serverInfo 11 }

  serverNFSEncryption  OBJECT-TYPE
      SYNTAX      OnOffValue
      MAX-ACCESS  read-write
      STATUS      current
      DESCRIPTION
              "Determines if the data sent to the NFS host is sent encrypted
               or in the clear across the LAN. The default is set of Off.
               NOTE: When NFS encryption is enabled, the Decoder utility
               software is required to be installed on the NFS host for
               decrypting the data to a readable format."
      ::= { serverInfo 12 }


  serverPortMenuString OBJECT-TYPE
      SYNTAX      DisplayString(SIZE(0..8))
      MAX-ACCESS  read-write
      STATUS      current
      DESCRIPTION
              "The string (up to 8 characters) used by a a session connected
               to a serial port to display the port buffer for that particular
               serial port. You can specify control (unprintable) codes by
               putting the decimal value in angle brackets < > (for example,
               Escape b is <027>b). The default is ~view."
      ::= { serverInfo 13 }


  serverBreakEnabled OBJECT-TYPE
      SYNTAX      OnOffValue
      MAX-ACCESS  read-write
      STATUS      current
      DESCRIPTION
              "Enables/disables proprietary inband SSH break signal processing 
              as well as the existing Reverse Telnet break signal. This parameter
              can also enable/disable the out-of-band break signals for TruePort. 
              The default value is Off.."
      ::= { serverInfo 15 }


  serverBanner OBJECT-TYPE
      SYNTAX      OnOffValue
      MAX-ACCESS  read-write
      STATUS      current
      DESCRIPTION
              "If enabled, displays a product identification banner before
               login prompts. Default is off."
      ::= { serverInfo 16 }

  serverSecurity OBJECT-TYPE
      SYNTAX      OnOffValue
      MAX-ACCESS  read-write
      STATUS      current
      DESCRIPTION
              "If enabled, the server will only respond to, and allow access
               to and from, the IP addresses of hosts configured in the hosts
               table."
      ::= { serverInfo 17 }

  serverPromptWithName OBJECT-TYPE
      SYNTAX      OnOffValue
      MAX-ACCESS  read-write
      STATUS      current
      DESCRIPTION
              "If enabled, the Device Server name will be included in login prompts,
               command line prompts, etc."
      ::= { serverInfo 18 }

  serverPasswordLimit OBJECT-TYPE
      SYNTAX      Integer32(0..10)
      MAX-ACCESS  read-write
      STATUS      current
      DESCRIPTION
              "The number of attempts a user is allowed to enter a password
               for a port. If this limit is exceeded, the port is disabled
               for 5 minutes. A user with Admin level rights can restart the
               port, bypassing the timeout, by issuing a kill on the disabled
               port. The default value is 3."
      ::= { serverInfo 19 }

  serverOemLogin OBJECT-TYPE
      SYNTAX      OnOffValue
      MAX-ACCESS  read-write
      STATUS      current
      DESCRIPTION
              "When set, and a custom language file is in use,
               the login prompt will use the string defined in the
               language file as the login prompt instead of the default prompt, login:."
      ::= { serverInfo 20 }

  serverBypassPassword OBJECT-TYPE
      SYNTAX      OnOffValue
      MAX-ACCESS  read-write
      STATUS      current
      DESCRIPTION
              "When set, authorized users who do not have a password set,
               with the exception of the Admin user, WILL NOT be prompted
               for a password at login with Local Authentication."
      ::= { serverInfo 21}

  serverSingleTelnet OBJECT-TYPE
      SYNTAX      OnOffValue
      MAX-ACCESS  read-write
      STATUS      current
      DESCRIPTION
              "Sets all reverse connections to a one connection at a time mode.
               Server-side applications will get a (socket) connection refused until:
               All data from previous connections on that serial port has drained,
               There are no other connections,
               Up to a 1 second interconnection poll timer has expired
               This also enables a per-connection keepalive TCP keepalive feature.
               After approximately 3 minutes of network connection idle time, the
               connection will send a gratuitous ACK to the network peer, thus
               either ensuring the connection stays active OR causing a dropped
               connection condition to be recognized by the reverse service
               (all connections)."
      ::= { serverInfo 22 }

  serverFlushOnClose OBJECT-TYPE
      SYNTAX      OnOffValue
      MAX-ACCESS  read-write
      STATUS      current
      DESCRIPTION
              "When enabled, deletes any pending data when a port is closed;
               as opposed to maintaining the port to send pending data.
               Default is Off."
      ::= { serverInfo 23 }

  serverPrimaryAuthMethod OBJECT-TYPE
     SYNTAX INTEGER {
        local(1),
        radius(2),
        kerberos(3),
        ldap(4),
        tacacs(5),
        securid(6),
        nis(7)
     }
     MAX-ACCESS  read-write
     STATUS      current
     DESCRIPTION
              "The first authentication method that the Device Server attempts.
               Some type of authentication must be done by the Device Server."
     ::= { serverInfo 24 }

  serverSecondaryAuthMethod OBJECT-TYPE
     SYNTAX      INTEGER {
        none(1),
        local(2),
        radius(3),
        kerberos(4),
        ldap(5),
        tacacs(6),
        securid(7),
        nis(8)
     }
     MAX-ACCESS  read-write
     STATUS      current
     DESCRIPTION
              "If the Primary Authentication Method fails, the next
               authentication method that the Device Server attempts. You
               can choose to use authentication methods in combination.
               For example, you can specify the Primary Authentication
               Method as Local and the Secondary Authentication Method as
               RADIUS. Therefore, some users can be defined in the Device
               Server (Local) others in RADIUS."
     ::= { serverInfo 25 }

  serverEthernetSpeedDuplex OBJECT-TYPE
      SYNTAX      INTEGER {
             speedAuto(1),
             speed10Half(2),
             speed10Full(3),
             speed100Half(4),
             speed100Full(5),
             speed1000Full(7),
			 sfpHalfDuplex(8),
			 sfpFullDuplex(9)
        }
      MAX-ACCESS  read-write
      STATUS      current
      DESCRIPTION
              "Define the Ethernet connection speed at one of the following:
               automatically detects the Ethernet interface speed and duplex
               10 Mbps Half Duplex
               10 Mbps Full Duplex
               100 Mbps Half Duplex
               100 Mbps Full Duplex
               1000 Mbps Full Duplex
               Half duplex for sfp module
               Full duplex for sfp module"
      ::= { serverInfo 26 }

  serverTFTPRetry OBJECT-TYPE
      SYNTAX      Integer32(0..5)
      MAX-ACCESS  read-write
      STATUS      current
      DESCRIPTION
              "The number of times the Device Server will attempt to
               transfer (using TFTP) a file to/from a host. Default is 5.
               A value of 0 (zero) means that the Device Server will not
               attempt a retry should TFTP fail."
      ::= { serverInfo 27 }

  serverTFTPTimeOut OBJECT-TYPE
      SYNTAX      Integer32(3..10)
      MAX-ACCESS  read-write
      STATUS      current
      DESCRIPTION
              "The time, in seconds, that the Device Server will wait for
               a successful transmit or receipt of TFTP packets before retrying
               a TFTP transfer. Default is 3 seconds."
      ::= { serverInfo 28 }

  serverEnableGuestLogin OBJECT-TYPE
      SYNTAX      OnOffValue
      MAX-ACCESS  read-write
      STATUS      current
      DESCRIPTION
              "Allow users who are not defined in the User database to log 
               into the Device Server with any user ID and the specified password.
               Guest users inherit their settings from the Default User's 
               configuration."
      ::= { serverInfo 29 }
      
  serverSecondaryIPaddress OBJECT-TYPE
      SYNTAX      IpAddress
      MAX-ACCESS  read-write
      STATUS      current
      DESCRIPTION
              "The Device Server's eth2 IPv4 network IP address.
               If you are using the Device Server in an IPv6 network,
               this field can be left blank."
      ::= { serverInfo 30 }

  serverSecondarySubnetBits OBJECT-TYPE
      SYNTAX      Integer32(0..32)
      MAX-ACCESS  read-write
      STATUS      current
      DESCRIPTION
              "The number of bits in the eth2 subnet mask. For example,
               a subnet mask of 255.255.0.0 has 16 subnet/prefix bits.
               Valid values are 0-32. The default is 0. When the value
               is 0, the correct value is determined based on the class
               of the IP Address."
      ::= { serverInfo 31 }
   serverEthSecondarySpeedDuplex OBJECT-TYPE
      SYNTAX      INTEGER {
             speedAuto(1),
             speed10Half(2),
             speed10Full(3),
             speed100Half(4),
             speed100Full(5),
             speed1000Full(7),
			 sfpHalfDuplex(8),
			 sfpFullDuplex(9)
        }    
      MAX-ACCESS  read-write
      STATUS      current
      DESCRIPTION
              "Define the Ethernet connection speed at one of the following:
               automatically detects the Ethernet interface speed and duplex
               10 Mbps Half Duplex
               10 Mbps Full Duplex
               100 Mbps Half Duplex
               100 Mbps Full Duplex
               1000 Mbps Full Duplex
               Half duplex for sfp module
               Full duplex for sfp module
               Note: 1000 Mbps is not supported on certain models"
      ::= { serverInfo 32 }      

  serverDHCPUpdateDNSPrimary OBJECT-TYPE
      SYNTAX      OnOffValue
      MAX-ACCESS  read-write
      STATUS      current
      DESCRIPTION
              "If enabled, the DNS server will be updated after the device server gets the
               IP address via DHCP."
      ::= { serverInfo 33 }

  serverPowerManagementMenuString OBJECT-TYPE
      SYNTAX      DisplayString(SIZE(0..8))
      MAX-ACCESS  read-write
      STATUS      current
      DESCRIPTION
              "Menu String for power management ."
      ::= { serverInfo 34 }
      
  serverActiveStandbyEnabled OBJECT-TYPE
      SYNTAX      OnOffValue
      MAX-ACCESS  read-write
      STATUS      current
      DESCRIPTION
              "Enable/disable active standby."
      ::= { serverInfo 35}
      
  serverActiveStandbyMiimon OBJECT-TYPE
      SYNTAX      Integer32(0..9999)
      MAX-ACCESS  read-write
      STATUS      current
      DESCRIPTION
              "Time in msec for frequency in MII link monitoring."
      ::= { serverInfo 36}

  serverActiveStandbyUpdelay OBJECT-TYPE
      SYNTAX      Integer32(0..9999)
      MAX-ACCESS  read-write
      STATUS      current
      DESCRIPTION
              "Delay in enabling a link after the 'link up' status has been detected"
      ::= { serverInfo 37}
      
  serverDropSessionDetectionTime OBJECT-TYPE
      SYNTAX      Integer32(1..32767)
      MAX-ACCESS  read-write
      STATUS      current
      DESCRIPTION
              "Dropped session detection time"
      ::= { serverInfo 38}    
      
  serverAutoObtainDNS OBJECT-TYPE
      SYNTAX      OnOffValue
      MAX-ACCESS  read-write
      STATUS      current
      DESCRIPTION
              "If enabled, the DNS server IP address will be get automatically via DHCP."
      ::= { serverInfo 39 }
      
  serverAutoObtainWINS OBJECT-TYPE
      SYNTAX      OnOffValue
      MAX-ACCESS  read-write
      STATUS      current
      DESCRIPTION
              "If enabled, the WINS server IP address will be get automatically via DHCP."
      ::= { serverInfo 40 }     

  serverAutoObtainGW OBJECT-TYPE
      SYNTAX      OnOffValue
      MAX-ACCESS  read-write
      STATUS      current
      DESCRIPTION
              "If enabled, the default gateway IP address will be get automatically via DHCP."
      ::= { serverInfo 41 }
      
  serverAlwaysAttemptSecond OBJECT-TYPE
      SYNTAX      OnOffValue
      MAX-ACCESS  read-write
      STATUS      current
      DESCRIPTION
              "If enabled, the secondary authentication method will always be used."
      ::= { serverInfo 42 }     
      
  serverDHCPUpdateDNSSecondary OBJECT-TYPE
      SYNTAX      OnOffValue
      MAX-ACCESS  read-write
      STATUS      current
      DESCRIPTION
              "If enabled, the DNS server will be updated for the secondary Ethernet interface 
               after the device server gets the IP address via DHCP."
      ::= { serverInfo 43 }
      
 serverDomainPrefixPrimary OBJECT-TYPE
      SYNTAX      DisplayString(SIZE(0..7))
      MAX-ACCESS  read-write
      STATUS      current
      DESCRIPTION
              "The domain prefix for primary Ethernet interface of the Device Server."
      ::= { serverInfo 44 } 
      
 serverDomainPrefixSecondary OBJECT-TYPE
      SYNTAX      DisplayString(SIZE(0..7))
      MAX-ACCESS  read-write
      STATUS      current
      DESCRIPTION
              "The domain prefix for secondary Ethernet interface of the Device Server."
      ::= { serverInfo 45 }
  
 serverPortBufferSyslog OBJECT-TYPE
      SYNTAX      OnOffValue
      MAX-ACCESS  read-write
      STATUS      current
      DESCRIPTION
              "Output port buffer to syslog."
      ::= { serverInfo 46}        
 serverPortBufferKeyStroke OBJECT-TYPE
      SYNTAX      OnOffValue
      MAX-ACCESS  read-write
      STATUS      current
      DESCRIPTION
              "Turn on port buffer keystroke."
      ::= { serverInfo 47}      
 serverIpsecUseNat OBJECT-TYPE
      SYNTAX      OnOffValue
      MAX-ACCESS  read-write
      STATUS      current
      DESCRIPTION
              "Enable or disable NAT traversal for IPsec."
      ::= { serverInfo 48}      
      
  serverAutoObtainDNSV6 OBJECT-TYPE
      SYNTAX      OnOffValue
      MAX-ACCESS  read-write
      STATUS      current
      DESCRIPTION
              "If enabled, the DNS server IP address will be obtained automatically via DHCPv6."
      ::= { serverInfo 49 }
      
  serverAuthenticateAdminlocal OBJECT-TYPE
      SYNTAX      OnOffValue
      MAX-ACCESS  read-write
      STATUS      current
      DESCRIPTION
              "If enabled, admin user will be only authenticated locally."
      ::= { serverInfo 50 }
	  
  serverDisplayMotdWeb OBJECT-TYPE
      SYNTAX      OnOffValue
      MAX-ACCESS  read-write
      STATUS      current
      DESCRIPTION
              "If enabled, the WebManager will display message of the day."
      ::= { serverInfo 51 }
	  
  serverGenericWebLoginScreen OBJECT-TYPE
      SYNTAX      OnOffValue
      MAX-ACCESS  read-write
      STATUS      current
      DESCRIPTION
              "If enabled, the WebManager will not display device server's information on login screen."
      ::= { serverInfo 52 }
      
  serverNfsHostTunnel OBJECT-TYPE
      SYNTAX      DisplayString(SIZE(0..14))
      MAX-ACCESS  read-write
      STATUS      current
      DESCRIPTION
              "The HTTP tunnel associated with the port buffering NFS host."
      ::= { serverInfo 54}
  
  serverPortBufferSyslogLevel OBJECT-TYPE
      SYNTAX      INTEGER {
        emergency(1),
        alert(2),
        critical(3),
        error(4),
        warning(5),
        notice(6),
        informational(7),
        debug(8)
      }
      MAX-ACCESS  read-write
      STATUS      current
      DESCRIPTION
              "Specify the syslog level to use for port buffering"
      ::= { serverInfo 55 }
      
  serverEasyPortWebClient OBJECT-TYPE
      SYNTAX      INTEGER {
               java(1),
               javascript(2)
      }
      MAX-ACCESS  read-write
      STATUS      current
      DESCRIPTION
              "Specifies the telnet/SSH client for EasyPortWeb.  Select 'java'
               to use the Java applet client.  Select 'javascript' to use the 
               web browser-based client."
      ::= { serverInfo 56 }

  serverDataLoggingBufferSize OBJECT-TYPE
      SYNTAX      INTEGER 
      MAX-ACCESS  read-write
      STATUS      current
      DESCRIPTION
              "Specifies the buffer size for Data Logging."
      ::= { serverInfo 57 }

  serverDataLoggingOptions OBJECT-TYPE
      SYNTAX      INTEGER {
               pre-version43(1),
               loss-less(2)
      }
      MAX-ACCESS  read-write
      STATUS      current
      DESCRIPTION
              "Specifies whether data logging should be backword compatible with
               versions of firmware prior to Version 4.3."
      ::= { serverInfo 58 }

  serverKeepAliveRetries OBJECT-TYPE
      SYNTAX      INTEGER 
      MAX-ACCESS  read-write
      STATUS      current
      DESCRIPTION
              "Specifies the number of time the iolan will retry the TCP 
               keepalive message."
      ::= { serverInfo 59 }

  serverKeepAliveTimeout OBJECT-TYPE
      SYNTAX      INTEGER 
      MAX-ACCESS  read-write
      STATUS      current
      DESCRIPTION
              "Specifies the time to wait for a tcp keepalive message response."
      ::= { serverInfo 60 }
  
  serverEth0MTU OBJECT-TYPE
      SYNTAX      INTEGER 
      MAX-ACCESS  read-write
      STATUS      current
      DESCRIPTION
              "Specifies the size of the ethernet MTU."
      ::= { serverInfo 61 }
  
  serverEth1MTU OBJECT-TYPE
      SYNTAX      INTEGER 
      MAX-ACCESS  read-write
      STATUS      current
      DESCRIPTION
              "Specifies the size of the ethernet MTU."
      ::= { serverInfo 62 }
  
  serverTFTPHost OBJECT-TYPE
      SYNTAX      DisplayString(SIZE(0..14))
      MAX-ACCESS  read-write
      STATUS      current
      DESCRIPTION
              "The name of the TFTP host."
      ::= { serverInfo 63}

  serverTFTPTunnelName OBJECT-TYPE
      SYNTAX      DisplayString(SIZE(0..14))
      MAX-ACCESS  read-write
      STATUS      current
      DESCRIPTION
              "The name of the HTTP tunnel associated with this service."
      ::= { serverInfo 64 }
  
  serverSecurityRange OBJECT-TYPE
      SYNTAX      OnOffValue
      MAX-ACCESS  read-write
      STATUS      current
      DESCRIPTION
              "If enabled, the server will only respond to, and allow access
               to and from, the IP addresses of hosts configured in the range
               of IP addresses."
      ::= { serverInfo 65 }

  serverRangeStartIPaddress OBJECT-TYPE
      SYNTAX      IpAddress
      MAX-ACCESS  read-write
      STATUS      current
      DESCRIPTION
              "The start IP address of the range that the server will only respond
               to, and allow access to and from." 
      ::= { serverInfo 66 }

  serverRangeEndIPaddress OBJECT-TYPE
      SYNTAX      IpAddress
      MAX-ACCESS  read-write
      STATUS      current
      DESCRIPTION
              "The end IP address of the range that the server will only respond
               to, and allow access to and from." 
      ::= { serverInfo 67 }

  serverAccountLockOut OBJECT-TYPE
      SYNTAX      OnOffValue
      MAX-ACCESS  read-write
      STATUS      current
      DESCRIPTION
              "If enabled, the server will lock out the user after a number of 
               invalid login attempts."
      ::= { serverInfo 68 }

  serverLoginOnce OBJECT-TYPE
      SYNTAX      OnOffValue
      MAX-ACCESS  read-write
      STATUS      current
      DESCRIPTION
              "If enabled, the server will only allow a user to login once."
      ::= { serverInfo 69 }

  serverPasswordRules OBJECT-TYPE
      SYNTAX      OnOffValue
      MAX-ACCESS  read-write
      STATUS      current
      DESCRIPTION
              "If enabled, the server will enforce the password rules for
               the user password."
      ::= { serverInfo 70 }

  serverDisableWebCaching OBJECT-TYPE
      SYNTAX      OnOffValue
      MAX-ACCESS  read-write
      STATUS      current
      DESCRIPTION
              "If enabled, the server will disable caching in the web browser."
      ::= { serverInfo 71 }

  serverDisableIpForwarding OBJECT-TYPE
      SYNTAX      OnOffValue
      MAX-ACCESS  read-write
      STATUS      current
      DESCRIPTION
              "If enabled, the server will disable IP forwarding between
               ethernet interfaces."
      ::= { serverInfo 72 }

  serverSecurityRange2 OBJECT-TYPE
      SYNTAX      OnOffValue
      MAX-ACCESS  read-write
      STATUS      current
      DESCRIPTION
              "If enabled, the server will only respond to, and allow access
               to and from, the IP addresses of hosts configured in the range
               of IP addresses."
      ::= { serverInfo 73 }

  serverRangeStartIPaddress2 OBJECT-TYPE
      SYNTAX      IpAddress
      MAX-ACCESS  read-write
      STATUS      current
      DESCRIPTION
              "The start IP address of the range that the server will only respond
               to, and allow access to and from." 
      ::= { serverInfo 74 }

  serverRangeEndIPaddress2 OBJECT-TYPE
      SYNTAX      IpAddress
      MAX-ACCESS  read-write
      STATUS      current
      DESCRIPTION
              "The end IP address of the range that the server will only respond
               to, and allow access to and from." 
      ::= { serverInfo 75 }

  serverSecurityRange3 OBJECT-TYPE
      SYNTAX      OnOffValue
      MAX-ACCESS  read-write
      STATUS      current
      DESCRIPTION
              "If enabled, the server will only respond to, and allow access
               to and from, the IP addresses of hosts configured in the range
               of IP addresses."
      ::= { serverInfo 76 }

  serverRangeStartIPaddress3 OBJECT-TYPE
      SYNTAX      IpAddress
      MAX-ACCESS  read-write
      STATUS      current
      DESCRIPTION
              "The start IP address of the range that the server will only respond
               to, and allow access to and from." 
      ::= { serverInfo 77 }

  serverRangeEndIPaddress3 OBJECT-TYPE
      SYNTAX      IpAddress
      MAX-ACCESS  read-write
      STATUS      current
      DESCRIPTION
              "The end IP address of the range that the server will only respond
               to, and allow access to and from." 
      ::= { serverInfo 78 }

  serverSecurityRange4 OBJECT-TYPE
      SYNTAX      OnOffValue
      MAX-ACCESS  read-write
      STATUS      current
      DESCRIPTION
              "If enabled, the server will only respond to, and allow access
               to and from, the IP addresses of hosts configured in the range
               of IP addresses."
      ::= { serverInfo 79 }

  serverRangeStartIPaddress4 OBJECT-TYPE
      SYNTAX      IpAddress
      MAX-ACCESS  read-write
      STATUS      current
      DESCRIPTION
              "The start IP address of the range that the server will only respond
               to, and allow access to and from." 
      ::= { serverInfo 80 }

  serverRangeEndIPaddress4 OBJECT-TYPE
      SYNTAX      IpAddress
      MAX-ACCESS  read-write
      STATUS      current
      DESCRIPTION
              "The end IP address of the range that the server will only respond
               to, and allow access to and from." 
      ::= { serverInfo 81 }

  serverSecurityRange5 OBJECT-TYPE
      SYNTAX      OnOffValue
      MAX-ACCESS  read-write
      STATUS      current
      DESCRIPTION
              "If enabled, the server will only respond to, and allow access
               to and from, the IP addresses of hosts configured in the range
               of IP addresses."
      ::= { serverInfo 82 }

  serverRangeStartIPaddress5 OBJECT-TYPE
      SYNTAX      IpAddress
      MAX-ACCESS  read-write
      STATUS      current
      DESCRIPTION
              "The start IP address of the range that the server will only respond
               to, and allow access to and from." 
      ::= { serverInfo 83 }

  serverRangeEndIPaddress5 OBJECT-TYPE
      SYNTAX      IpAddress
      MAX-ACCESS  read-write
      STATUS      current
      DESCRIPTION
              "The end IP address of the range that the server will only respond
               to, and allow access to and from." 
      ::= { serverInfo 84 }

  serverSecurityRange6 OBJECT-TYPE
      SYNTAX      OnOffValue
      MAX-ACCESS  read-write
      STATUS      current
      DESCRIPTION
              "If enabled, the server will only respond to, and allow access
               to and from, the IP addresses of hosts configured in the range
               of IP addresses."
      ::= { serverInfo 85 }

  serverRangeStartIPaddress6 OBJECT-TYPE
      SYNTAX      IpAddress
      MAX-ACCESS  read-write
      STATUS      current
      DESCRIPTION
              "The start IP address of the range that the server will only respond
               to, and allow access to and from." 
      ::= { serverInfo 86 }

  serverRangeEndIPaddress6 OBJECT-TYPE
      SYNTAX      IpAddress
      MAX-ACCESS  read-write
      STATUS      current
      DESCRIPTION
              "The end IP address of the range that the server will only respond
               to, and allow access to and from." 
      ::= { serverInfo 87 }

-- -----------------------------------------------------------------------------
  serverIPaddress3 OBJECT-TYPE
      SYNTAX      IpAddress
      MAX-ACCESS  read-write
      STATUS      current
      DESCRIPTION
              "The Device Server's eth3 IPv4 network IP address.
               If you are using the Device Server in an IPv6 network,
               this field can be left blank."
      ::= { serverInfo 88 }

  serverSubnetBits3 OBJECT-TYPE
      SYNTAX      Integer32(0..32)
      MAX-ACCESS  read-write
      STATUS      current
      DESCRIPTION
              "The number of bits in the eth3 subnet mask. For example,
               a subnet mask of 255.255.0.0 has 16 subnet/prefix bits.
               Valid values are 0-32. The default is 0. When the value
               is 0, the correct value is determined based on the class
               of the IP Address."
      ::= { serverInfo 89 }

  serverDHCPUpdateDNS3 OBJECT-TYPE
      SYNTAX      OnOffValue
      MAX-ACCESS  read-write
      STATUS      current
      DESCRIPTION
              "If enabled, the DNS server will be updated for the third Ethernet interface 
               after the device server gets the IP address via DHCP."
      ::= { serverInfo 90 }
      
  serverDomainPrefix3 OBJECT-TYPE
      SYNTAX      DisplayString(SIZE(0..7))
      MAX-ACCESS  read-write
      STATUS      current
      DESCRIPTION
              "The domain prefix for third Ethernet interface of the Device Server."
      ::= { serverInfo 91 }
  
  serverEth3MTU OBJECT-TYPE
      SYNTAX      INTEGER 
      MAX-ACCESS  read-write
      STATUS      current
      DESCRIPTION
              "Specifies the size of the third Ethernet MTU."
      ::= { serverInfo 92 }
  
  serverEth1MediaType OBJECT-TYPE
      SYNTAX      INTEGER {
            comboAuto(1),
            comboRj45(2),
            comboSfp(3)
        }
        MAX-ACCESS  read-write
        STATUS      current
        DESCRIPTION
            "For combo ports, specifies the combo port mode. If not supported, this object is not writeable."
      ::= { serverInfo 93 }
  
  serverEth1Sgmii OBJECT-TYPE
      SYNTAX      OnOffValue
      MAX-ACCESS  read-write
      STATUS      current
      DESCRIPTION
            "For SFP ports, specifies whether this port has SGMII (Serial Gigibit Media 
            Independent Interface) configured. If not supported, this object is not writeable."
      ::= { serverInfo 94 }

  serverEth2MediaType OBJECT-TYPE
      SYNTAX      INTEGER {
            comboAuto(1),
            comboRj45(2),
            comboSfp(3)
        }
        MAX-ACCESS  read-write
        STATUS      current
        DESCRIPTION
            "For combo ports, specifies the combo port mode. If not supported, this object is not writeable."
      ::= { serverInfo 95 }
  
  serverEth2Sgmii OBJECT-TYPE
      SYNTAX      OnOffValue
      MAX-ACCESS  read-write
      STATUS      current
      DESCRIPTION
            "For SFP ports, specifies whether this port has SGMII (Serial Gigibit Media 
            Independent Interface) configured. If not supported, this object is not writeable."
      ::= { serverInfo 96 }
  
  
--******************************************************************************  
  --  hostsInfo group. A table of entries, each entry per IP host.

  hostsInfoTable OBJECT-TYPE
      SYNTAX      SEQUENCE OF HostsInfoEntry
      MAX-ACCESS  not-accessible
      STATUS      current
      DESCRIPTION
              "The hosts info table."
      ::= { hostsInfo 1 }

  hostsInfoEntry OBJECT-TYPE
      SYNTAX      HostsInfoEntry
      MAX-ACCESS  not-accessible
      STATUS      current
      DESCRIPTION
              "An entry in the hostsInfoTable, each relating to a host."
      INDEX   { hostIndex }
      ::= { hostsInfoTable 1 }

  HostsInfoEntry ::=
      SEQUENCE {
        hostIndex         GenericTableIndex,
        hostStatus        ContainerStatus,
        hostName          DisplayString,
        hostIpAddr        Ipv4v6Address,
        fqdn              DisplayString
      }

  hostIndex OBJECT-TYPE
      SYNTAX      GenericTableIndex
      MAX-ACCESS  not-accessible
      STATUS      current
      DESCRIPTION
              "The table entry number for this host."
      ::= { hostsInfoEntry 1 }

   hostStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { hostsInfoEntry 2 }

  hostName OBJECT-TYPE
      SYNTAX      DisplayString(SIZE(0..14))
      MAX-ACCESS  read-write
      STATUS      current
      DESCRIPTION
              "The host name used for this host entry.
               To delete an entry, blank out this field.
               If blank, this entry is currently unused."
      ::= { hostsInfoEntry 3 }

  hostIpAddr OBJECT-TYPE
      SYNTAX      Ipv4v6Address
      MAX-ACCESS  read-write
      STATUS      current
      DESCRIPTION
              "The host IP address used for this entry."
      ::= { hostsInfoEntry 4 }

   fqdn OBJECT-TYPE
      SYNTAX      DisplayString(SIZE(0..255))
      MAX-ACCESS  read-write
      STATUS      current
      DESCRIPTION
              "The host full qualified domain name for the host entry.
               If blank, this entry is currently unused."
      ::= { hostsInfoEntry 5 }

--  userInfo group. A table of entries, each entry per user.

  userTable OBJECT-TYPE
      SYNTAX      SEQUENCE OF UserEntry
      MAX-ACCESS  not-accessible
      STATUS      current
      DESCRIPTION
              "The user table."
      ::= { userInfo 1 }

  userEntry OBJECT-TYPE
      SYNTAX      UserEntry
      MAX-ACCESS  not-accessible
      STATUS      current
      DESCRIPTION
              "An entry in the userEntry, each relating to a user."
      INDEX   { userIndex }
      ::= { userTable 1 }

  UserEntry ::=
      SEQUENCE {
         userIndex                    GenericTableIndex,
         userStatus                   ContainerStatus,
         userName                     DisplayString,
         userService                  INTEGER,
         userLanguage                 INTEGER,
         userLevel                    INTEGER,
         userHotKeyPrefix             Hex8,
         userPhoneNumber              DisplayString,
         userCallBack                 OnOffValue,
         userIdleTimer                Integer32,
         userSessionTimer             Integer32,
         userIpHost                   Ipv4v6Address,
         userTelnetPort               Integer32,
         userSSHPort                  Integer32,
         userTcpClearPort             Integer32,
         userFramedIp                 IpAddress,
         userSubnetBits               Integer32,
         userIpv6InterfaceIdentifier  Ipv6InterfaceId,
         userFramedMtu                Integer32,
         userFramedCompression        OnOffValue,
         userRouting                  INTEGER,
         userPortConnected            Integer32,
         userSessionTime              Integer32,
         userIdleTime                 Integer32,
         userAllowAccessClusterPorts  OnOffValue,
         userHost                     DisplayString,
         userTunnel                   DisplayString
    }

  userIndex OBJECT-TYPE
      SYNTAX      GenericTableIndex
      MAX-ACCESS  not-accessible
      STATUS      current
      DESCRIPTION
              "The table entry number for this user."
      ::= { userEntry 1 }

   userStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { userEntry 2}

  userName OBJECT-TYPE
      SYNTAX      DisplayString(SIZE(0..16))
      MAX-ACCESS  read-write
      STATUS      current
      DESCRIPTION
              "The user name.
               To delete a user, set this field to blank.
               If blank, this entry is currently unused."
      ::= { userEntry 3 }

  userService OBJECT-TYPE
      SYNTAX      INTEGER {
        dsprompt(1),
        telnet(2),
        ssh(3),
        rlogin(4),
        slip(5),
        ppp(6),
        tcpclear(7),
        sslraw(8)
      }
      MAX-ACCESS  read-write
      STATUS      current
      DESCRIPTION
              "The type of service that the user will use:
               dsprompt, telnet, ssh, rlogin, slip, ppp, tcpclear
               or sslraw."
      ::= { userEntry 4 }

   userLanguage OBJECT-TYPE
      SYNTAX      INTEGER {
        english(1),
        custom(2)
      }
      MAX-ACCESS  read-write
      STATUS      current
      DESCRIPTION
              "Sets the language the user will view all Menu, CLI,
               and WebManager strings."
      ::= { userEntry 5 }

   userLevel OBJECT-TYPE
      SYNTAX      INTEGER {
        admin(1),
        normal(2),
        restricted(3),
        menu(4)
      }
      MAX-ACCESS  read-write
      STATUS      current
      DESCRIPTION
              "Admin-Total access to the Device Server. More than one admin user
               account can exist, but we recommend that you only have one.
               Normal-Limited access to the Device Server. Limited CLI commands
               and Menu access, can configure the user's own configuration settings.
               Restricted-Can only access predefined sessions or access the
               Easy Port Access menu. Can only view or monitor the Device Server
               using CLI commands to display information about the Device Server.
               Menu-Only access predefined sessions or access the Easy Port Access
               menu. The Easy Port Access allows the user to connect to the
               accessible line without disconnecting their initial connection to the
               Device Server. Does not have any access to CLI commands."
      ::= { userEntry 6}

   userHotKeyPrefix OBJECT-TYPE
      SYNTAX      Hex8
      MAX-ACCESS  read-write
      STATUS      current
      DESCRIPTION
              "The prefix that a user types to control the current session. The
               default value is hex 01, which corresponds to Ctrl-a (^a):
               ^a number-Switches from one session to another, press ^a and then
               the required session number. For example, ^a 2 would switch you to
               session 2. Pressing ^a 0 will return you to the Device Server Menu.
               ^a n-Display the next session. The current session will remain active.
               ^a p-Display the previous session. The current session will remain active.
               ^a m-To exit a session and return to the Device Server. You will be
               returned to where you left off. The session will be left running.
               ^a l-(Lowercase L) Locks the line until the user unlocks it. The user
               is prompted for a password and locks the line. Next, the user must
               retype the password to unlock the line.
               ^r-Redraws the screen."
      ::= { userEntry 7}

   userPhoneNumber OBJECT-TYPE
      SYNTAX      DisplayString(SIZE(0..32))
      MAX-ACCESS  read-write
      STATUS      current
      DESCRIPTION
              "The phone number the Device Server will dial to callback the user
               (you must have set Callback to On). Enter the number without spaces."
      ::= { userEntry 8}

   userCallBack OBJECT-TYPE
      SYNTAX      OnOffValue
      MAX-ACCESS  read-write
      STATUS      current
      DESCRIPTION
              "When On, enter a phone number for the Device Server to call the user
               back (the Callback parameter is unrelated to the Line Dial parameter).
               Note: the Device Server will allow callback only when a user is
               authenticated. If the protocol over the link does not provide
               authentication, there will be no callback. Therefore, when the Line
               Service is set to PPP, you must use either PAP or CHAP, because these
               protocols provide authentication. The default is Off. The Device Server
               supports another type of callback, Roaming Callback, which is
               configurable when the Line Service is set to PPP."
      ::= { userEntry 9}

   userIdleTimer OBJECT-TYPE
      SYNTAX      Integer32(0..4294967)
      MAX-ACCESS  read-write
      STATUS      current
      DESCRIPTION
              "The amount of time, in seconds, that the Idle Timer will run. Use
               this timer to close a connection because of inactivity. When the
               Idle Timer expires, because there has been no exchange of data within
               the specified time, the Device Server will close the connection. The
               default is 0 (zero), meaning that the Idle Timer will not expire
               (the connection is open permanently)."
      ::= { userEntry 10}

   userSessionTimer OBJECT-TYPE
      SYNTAX      Integer32(0..4294967)
      MAX-ACCESS  read-write
      STATUS      current
      DESCRIPTION
              "The amount of time, in seconds, that the Session Timer will run. Use
               this timer to forcibly close a user's session (connection). When the
               Session Timer expires, the Device Server will end the connection. The
               default is 0 (zero), meaning that the session timer will not expire
               (the session is open permanently, or until the user logs out)."
      ::= { userEntry 11}

   userIpHost OBJECT-TYPE
      SYNTAX      Ipv4v6Address
      MAX-ACCESS  read-write
      STATUS      current
      DESCRIPTION
              "When the User Service is set to Telnet, TCP_clear or SSL_RAW, the target
               host IP address. If 255.255.255.255 is specified in the configuration,
               the user will be prompted for an IP address or host name. If no IP
               address is specified, the Host IP value in the Default User configuration
               will be used. The default is 0.0.0.0."
      ::= { userEntry 12}

   userTelnetPort OBJECT-TYPE
      SYNTAX      Integer32(0..65535)
      MAX-ACCESS  read-write
      STATUS      current
      DESCRIPTION
              "The TCP port number for the Telnet session."
      ::= { userEntry 13}

   userSSHPort OBJECT-TYPE
      SYNTAX      Integer32(0..65535)
      MAX-ACCESS  read-write
      STATUS      current
      DESCRIPTION
              "The TCP port number for the SSH session."
      ::= { userEntry 14}

   userTcpClearPort OBJECT-TYPE
      SYNTAX      Integer32(0..65535)
      MAX-ACCESS  read-write
      STATUS      current
      DESCRIPTION
              "The TCP port number for the TCP-Clear or SSL-Raw session."
      ::= { userEntry 15}

   userFramedIp OBJECT-TYPE
      SYNTAX      IpAddress
      MAX-ACCESS  read-write
      STATUS      current
      DESCRIPTION
              "Used for User Service PPP or SLIP, sets the IP address of the
               remote user. Enter the address in dot decimal notation as follows:
               255.255.255.254 (default)-The Device Server will use the Remote
                  IP Address set in the PPP settings for the line.
               255.255.255.255-When the User Service is PPP, the Device Server will
                  allow the remote machine to specify its IP address (overriding
                  the IP address negotiation value configured in the PPP settings).
               255.255.255.255-When the User Service is SLIP, the Device Server will
                  use the Remote IP Address set for the line (no negotiation).
               n.n.n.n-(where n is a number) Enter the IP address of your choice.
                  This IP address will then be used in preference to the Remote IP
                  Address set for a line."
      ::= { userEntry 16}

   userSubnetBits OBJECT-TYPE
      SYNTAX      Integer32(0..32)
      MAX-ACCESS  read-write
      STATUS      current
      DESCRIPTION
              "(IPv4 only) If the remote user is on a subnet, enter the number of
               bits in the subnet mask. For example, a subnet mask of 255.255.0.0
               has 16 subnet/prefix bits."
      ::= { userEntry 17}

   userIpv6InterfaceIdentifier OBJECT-TYPE
      SYNTAX      Ipv6InterfaceId
      MAX-ACCESS  read-write
      STATUS      current
      DESCRIPTION
              "Used for User Service PPP, sets the IP address of the remote user.
               Enter the address in IPv6 format. The first 64 bits of the Interface
               Identifier must be zero, therefore, ::abcd:abcd:abcd:abcd is the
               expected format."
      ::= { userEntry 18}

   userFramedMtu OBJECT-TYPE
      SYNTAX      Integer32(64..1500)
      MAX-ACCESS  read-write
      STATUS      current
      DESCRIPTION
              "Used for User Service PPP or SLIP, specifies the maximum size of
               packets, in bytes, being transferred across the link. On noisy
               links it might be preferable to fragment large packets being
               transferred over the link, since there will be quicker recovery
               from errors. Depending on whether you have selected a User Service
               of SLIP or PPP, details are as follows:
               PPP-Framed MTU will be the maximum size of packets that the Device
                  Server port will accept. This value is negotiated between the
                  two ends of the link. The valid range is 64-1500. The default
                  is 1500 bytes.
               SLIP-Framed MTU will be the maximum size of packets being sent by
                  the Device Server. The Device Server will send SLIP packets in
                  the range 256-1006 bytes. The default value is 256 bytes.
               The Framed MTU value will be used in preference to the MTU/MRU values
               set for a Line."
      ::= { userEntry 19}

   userFramedCompression OBJECT-TYPE
      SYNTAX      OnOffValue
      MAX-ACCESS  read-write
      STATUS      current
      DESCRIPTION
              "Used for User Service PPP or SLIP, determines whether Van Jacobsen
               Compression is used on the link. VJ compression is a means of reducing
               the standard TCP/IP header from 40 octets to approximately 5 octets.
               This gives a significant performance improvement, particularly when
               interactive applications are being used. For example, when the user is
               typing, a single character can be passed over the link with a 40 octet
               header attached. VJ Compression has little effect on other types of links,
               such as FTP, where the packets are much larger. The Framed Compression
               value will be used in preference to the VJ Compression value set for a
               Line. The default is Off."
      ::= { userEntry 20}

   userRouting OBJECT-TYPE
      SYNTAX      INTEGER {
        none(1),
        send(2),
        listen(3),
        sendAndListen(4)
      }
      MAX-ACCESS  read-write
      STATUS      current
      DESCRIPTION
              "Determines the routing mode used for RIP packets on the PPP and SLIP
               interfaces. Values are:
               None-RIP packets are neither received nor sent by the Device Server.
               Send-RIP packets can only be sent by the Device Server.
               Listen-RIP packets can only be received by the Device Server.
               Send and Listen-RIP packets are sent and received by the Device Server."
      ::= { userEntry 21}

    
    
    userPortConnected OBJECT-TYPE
      SYNTAX Integer32(-1..2147483647)
      MAX-ACCESS  read-only
      STATUS      current
      DESCRIPTION
              "Port user is currently connected to. -1 if user not connected"
      ::= { userEntry 22}

    userSessionTime OBJECT-TYPE
      SYNTAX Integer32(0..4294967)
      MAX-ACCESS  read-only
      STATUS      current
      DESCRIPTION
              "Current User session time."
      ::= { userEntry 23}

    userIdleTime OBJECT-TYPE
      SYNTAX Integer32(0..4294967)
      MAX-ACCESS  read-only
      STATUS      current
      DESCRIPTION
              "Current Idle time"
      ::= { userEntry 24}

     --  ::= ::= { userEntry 25}        this OID is obsolete
     --  ::= ::= { userEntry 26}        this OID is obsolete

    userAllowAccessClusterPorts OBJECT-TYPE
      SYNTAX      OnOffValue
      MAX-ACCESS  read-write
      STATUS      current
      DESCRIPTION
              "Allow/disallow the user to access to clustering ports."
      ::= { userEntry 27 }
      
    userHost OBJECT-TYPE
      SYNTAX      DisplayString (SIZE(0..14))
      MAX-ACCESS  read-write
      STATUS      current
      DESCRIPTION
              "The name of the host."
      ::= { userEntry 28}  

    userTunnel OBJECT-TYPE
      SYNTAX      DisplayString (SIZE(0..14))
      MAX-ACCESS  read-write
      STATUS      current
      DESCRIPTION
              "The HTTP tunnel associated with the user's host."
      ::= { userEntry 29}  

-- Port Access Table

  portAccessTable OBJECT-TYPE
      SYNTAX      SEQUENCE OF PortAccessEntry
      MAX-ACCESS  not-accessible
      STATUS      current
      DESCRIPTION
              "The port access info table for user."
      ::= { userInfo 2 }

  portAccessEntry OBJECT-TYPE
      SYNTAX      PortAccessEntry
      MAX-ACCESS  not-accessible
      STATUS      current
      DESCRIPTION
              "An entry in the portAccessTable, each relating to a user's
               access privileges for a serial port."
      INDEX   { portAccessUserIndex, portAccessPortIndex }
      ::= { portAccessTable 1 }

  PortAccessEntry ::=
      SEQUENCE {
         portAccessUserIndex    GenericTableIndex,
         portAccessPortIndex    PortNumber,
         portAccessStatus       ContainerStatus,
         portRWAccessAllowed    YesNoValue,
         portRIAccessAllowed    YesNoValue,
         portROAccessAllowed    YesNoValue
      }
      
  portAccessUserIndex OBJECT-TYPE
      SYNTAX      GenericTableIndex
      MAX-ACCESS  not-accessible
      STATUS      current
      DESCRIPTION
              "The index for the user entry that port access applies to."
      ::= { portAccessEntry 1 }
  portAccessPortIndex OBJECT-TYPE
      SYNTAX      PortNumber
      MAX-ACCESS  not-accessible
      STATUS      current
      DESCRIPTION
              "The port number that user access applies to."
      ::= { portAccessEntry 2 }

   portAccessStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portAccessEntry 3 }

  portRWAccessAllowed OBJECT-TYPE
      SYNTAX      YesNoValue
      MAX-ACCESS  read-write
      STATUS      current
      DESCRIPTION
              "Enable or disable the user's read write access to the port."
      ::= { portAccessEntry 4 }

  portRIAccessAllowed OBJECT-TYPE
      SYNTAX      YesNoValue
      MAX-ACCESS  read-write
      STATUS      current
      DESCRIPTION
              "Enable or disable the user's read input access to the port."
      ::= { portAccessEntry 5 }

  portROAccessAllowed OBJECT-TYPE
      SYNTAX      YesNoValue
      MAX-ACCESS  read-write
      STATUS      current
      DESCRIPTION
              "Enable or disable the user's read output access to the port."
      ::= { portAccessEntry 6 }


-- User Session Table


  userSessionTable OBJECT-TYPE
      SYNTAX      SEQUENCE OF UserSessionEntry
      MAX-ACCESS  not-accessible
      STATUS      current
      DESCRIPTION
              "user."
      ::= { userInfo 3 }

  userSessionEntry OBJECT-TYPE
      SYNTAX      UserSessionEntry
      MAX-ACCESS  not-accessible
      STATUS      current
      DESCRIPTION
              "An entry in the userEntry, each relating to a user."
      INDEX   { userSessionUserIndex, userSessionNumber  }
      ::= { userSessionTable 1 }

  UserSessionEntry ::=
      SEQUENCE {
        userSessionUserIndex           GenericTableIndex,
        userSessionNumber               Integer32,
        userSessionStatus               ContainerStatus,
        userSessionType                 INTEGER,
        userSessionAuto                 OnOffValue,
        userSessionTelnetPort           Integer32,
        userSessionTelnetHost           DisplayString,
        userSessionTelnetTermType       DisplayString,
        userSessionTelnetEcho           OnOffValue,
        userSessionTelnetMapnl          OnOffValue,
        userSessionTelnetMode           OnOffValue,
        userSessionTelnetInterrupt      Hex8,
        userSessionTelnetQuit           Hex8,
        userSessionTelnetEOF            Hex8,
        userSessionTelnetErase          Hex8,
        userSessionTelnetEchoCC         Hex8,
        userSessionTelnetBreak          Hex8,
        userSessionSSHPort              Integer32,
        userSessionSSHHost              DisplayString,
        userSessionSSHTermType          DisplayString,
        userSessionSSHVerbose           OnOffValue,
        userSessionSSHCompression       OnOffValue,
        userSessionSSHAutoLogin         OnOffValue,
        userSessionSSHName              DisplayString,
        userSessionSSHProtocol          INTEGER,
        userSessionSSHRSA               OnOffValue,
        userSessionSSHDSA               OnOffValue,
        userSessionSSHKeyboard          OnOffValue,
        userSessionSSHCipherSSH1        INTEGER,
        userSessionSSHFirstSSH2Cipher   INTEGER,
        userSessionSSHSecondSSH2Cipher  INTEGER,
        userSessionSSHThirdSSH2Cipher   INTEGER,
        userSessionSSHFourthSSH2Cipher  INTEGER,
        userSessionSSHFifthSSH2Cipher   INTEGER,
        userSessionRloginHost           DisplayString,
        userSessionRloginTermType       DisplayString,
        userSessionTelnetTunnelName     DisplayString,
        userSessionSSHTunnelName        DisplayString,
        userSessionRloginTunnelName     DisplayString,
        userSessionStrictHostKeyChecking OnOffValue,
        userSessionSSHSixthSSH2Cipher   INTEGER,
         userSessionSSHSeventhSSH2Cipher   INTEGER,
         userSessionSSHEighthSSH2Cipher   INTEGER
       }
  userSessionUserIndex OBJECT-TYPE
      SYNTAX      GenericTableIndex
      MAX-ACCESS  not-accessible
      STATUS      current
      DESCRIPTION
              "The user number."
      ::= { userSessionEntry 1 }

  userSessionNumber OBJECT-TYPE
      SYNTAX      Integer32(1..4)
      MAX-ACCESS  not-accessible
      STATUS      current
      DESCRIPTION
              "The session number."
      ::= { userSessionEntry 2 }

   userSessionStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { userSessionEntry 3}

  userSessionType OBJECT-TYPE
      SYNTAX      INTEGER {
        none(1),
        telnet(2),
        rlogin(3),
        ssh(4)
      }
      MAX-ACCESS  read-write
      STATUS      current
      DESCRIPTION
              "The type of session for this session number for this user."
      ::= { userSessionEntry 4 }

  userSessionAuto OBJECT-TYPE
      SYNTAX      OnOffValue
      MAX-ACCESS  read-write
      STATUS      current
      DESCRIPTION
              "Specify whether or not the session(s) will start automatically
               when the user logs into the Device Server. "
      ::= { userSessionEntry 5 }

  userSessionTelnetPort OBJECT-TYPE
      SYNTAX      Integer32(0..65535)
      MAX-ACCESS  read-write
      STATUS      current
      DESCRIPTION
              "For Telnet sessions, the TCP port number the target host is
               listening on for incoming connections."
      ::= { userSessionEntry 6 }

  userSessionTelnetHost OBJECT-TYPE
      SYNTAX      DisplayString(SIZE(0..14))
      MAX-ACCESS  read-write
      STATUS      current
      DESCRIPTION
              "The name of the target host."
      ::= { userSessionEntry 7 }

  userSessionTelnetTermType OBJECT-TYPE
      SYNTAX      DisplayString(SIZE(0..14))
      MAX-ACCESS  read-write
      STATUS      current
      DESCRIPTION
              "Type of terminal attached to this line; for example, ANSI or WYSE60."
      ::= { userSessionEntry 8 }

  userSessionTelnetEcho OBJECT-TYPE
      SYNTAX      OnOffValue
      MAX-ACCESS  read-write
      STATUS      current
      DESCRIPTION
              "Toggles between local echo of entered characters and suppressing local
               echo. Local echo is used for normal processing, while suppressing the
               echo is convenient for entering text that should not be displayed on
               the screen, such as passwords. This parameter can only be used when
               Line Mode is On. Default is Off."
      ::= { userSessionEntry 9}

  userSessionTelnetMapnl OBJECT-TYPE
      SYNTAX      OnOffValue
      MAX-ACCESS  read-write
      STATUS      current
      DESCRIPTION
              "Maps carriage returns (CR) to carriage return line feed (CRLF). Default is Off."
      ::= { userSessionEntry 10}

  userSessionTelnetMode OBJECT-TYPE
      SYNTAX      OnOffValue
      MAX-ACCESS  read-write
      STATUS      current
      DESCRIPTION
              "When On, keyboard input is not sent to the remote host until Enter is
               pressed, otherwise input is sent every time a key is pressed. Default is Off."
      ::= { userSessionEntry 11}

  userSessionTelnetInterrupt OBJECT-TYPE
      SYNTAX      Hex8
      MAX-ACCESS  read-write
      STATUS      current
      DESCRIPTION
              "Defines the interrupt character. Typing the interrupt character interrupts
               the current process. This value is in hexadecimal with a default value
               of 3 (ASCII value ^C)."
      ::= { userSessionEntry 12 }

  userSessionTelnetQuit OBJECT-TYPE
      SYNTAX      Hex8
      MAX-ACCESS  read-write
      STATUS      current
      DESCRIPTION
              "Defines the quit character. Typing the quit character closes and exits the
               current Telnet session. This value is in hexadecimal with a default value
               of 1c (ASCII value FS)."
      ::= { userSessionEntry 13}

  userSessionTelnetEOF OBJECT-TYPE
      SYNTAX      Hex8
      MAX-ACCESS  read-write
      STATUS      current
      DESCRIPTION
              "Defines the end-of-file character. When Line Mode is On, entering the eof
               character as the first character on a line sends the character to the remote
               host. This value is in hexadecimal with a default value of 4 (ASCII value ^D)."
      ::= { userSessionEntry 14 }

  userSessionTelnetErase OBJECT-TYPE
      SYNTAX      Hex8
      MAX-ACCESS  read-write
      STATUS      current
      DESCRIPTION
              "Defines the erase character. When Line Mode is Off, typing the erase character
               erases one character. This value is in hexadecimal with a default value of 8
               (ASCII value ^H)."
      ::= { userSessionEntry 15 }

  userSessionTelnetEchoCC OBJECT-TYPE
      SYNTAX      Hex8
      MAX-ACCESS  read-write
      STATUS      current
      DESCRIPTION
              "Defines the echo character. When Line Mode is On, typing the echo character
               echoes the text locally and sends only completed lines to the host. This
               value is in hexadecimal with a default value of 5 (ASCII value ^E)."
      ::= { userSessionEntry 16 }

  userSessionTelnetBreak OBJECT-TYPE
      SYNTAX      Hex8
      MAX-ACCESS  read-write
      STATUS      current
      DESCRIPTION
              "Defines the escape character. Returns you to the command line mode.
               This value is in hexadecimal with a default value of 1d (ASCII value GS)."
      ::= { userSessionEntry 17}

  userSessionSSHPort OBJECT-TYPE
      SYNTAX      Integer32(0..65535)
      MAX-ACCESS  read-write
      STATUS      current
      DESCRIPTION
              "The target host TCP port number."
      ::= { userSessionEntry 18}

  userSessionSSHHost OBJECT-TYPE
      SYNTAX      DisplayString(SIZE(0..14))
      MAX-ACCESS  read-write
      STATUS      current
      DESCRIPTION
              "The host that the user will automatically connect to via SSH
               after a successful login."
      ::= { userSessionEntry 19}

  userSessionSSHTermType OBJECT-TYPE
      SYNTAX      DisplayString(SIZE(0..14))
      MAX-ACCESS  read-write
      STATUS      current
      DESCRIPTION
              "The type of terminal that will connecting via SSH."
      ::= { userSessionEntry 20}

  userSessionSSHVerbose OBJECT-TYPE
      SYNTAX      OnOffValue
      MAX-ACCESS  read-write
      STATUS      current
      DESCRIPTION
              "Displays debug messages on the terminal."
      ::= { userSessionEntry 21}

  userSessionSSHCompression OBJECT-TYPE
      SYNTAX      OnOffValue
      MAX-ACCESS  read-write
      STATUS      current
      DESCRIPTION
              "Requests compression of all data. Compression is desirable
               on modem lines and other slow connections, but will only
               slow down things on fast networks."
      ::= { userSessionEntry 22}

  userSessionSSHAutoLogin OBJECT-TYPE
      SYNTAX      OnOffValue
      MAX-ACCESS  read-write
      STATUS      current
      DESCRIPTION
              "Creates an automatic SSH login, using the Name and Password values."
      ::= { userSessionEntry 23}

  userSessionSSHName OBJECT-TYPE
      SYNTAX      DisplayString(SIZE(0..20))
      MAX-ACCESS  read-write
      STATUS      current
      DESCRIPTION
              "The name of the user logging into the SSH session."
      ::= { userSessionEntry 24}

  userSessionSSHProtocol OBJECT-TYPE
      SYNTAX      INTEGER {
        ssh1(1),
        ssh2(2),
        sshBoth(3)
      }
      MAX-ACCESS  read-write
      STATUS      current
      DESCRIPTION
              "Specify the SSH client version that will be used
               for the SSH session."
      ::= { userSessionEntry 25}

  userSessionSSHRSA OBJECT-TYPE
      SYNTAX      OnOffValue
      MAX-ACCESS  read-write
      STATUS      current
      DESCRIPTION
              "An authentication method used by SSH version 1 and 2.
               Use RSA authentication for the SSH session."
      ::= { userSessionEntry 26}

  userSessionSSHDSA OBJECT-TYPE
      SYNTAX      OnOffValue
      MAX-ACCESS  read-write
      STATUS      current
      DESCRIPTION
              "An authentication method used by SSH version 2.
               Use DSA authentication for the SSH session."
      ::= { userSessionEntry 27}

  userSessionSSHKeyboard OBJECT-TYPE
      SYNTAX      OnOffValue
      MAX-ACCESS  read-write
      STATUS      current
      DESCRIPTION
              "The user types in a password for authentication."
      ::= { userSessionEntry 28}

  userSessionSSHCipherSSH1 OBJECT-TYPE
      SYNTAX      INTEGER {
        tripledes(1),
        blowfish(2)
      }
      MAX-ACCESS  read-write
      STATUS      current
      DESCRIPTION
              "Select the encryption method (cipher) that you
               want to use for your SSH version 1 connection:
               3DES or Blowfish"
      ::= { userSessionEntry 29}

  userSessionSSHFirstSSH2Cipher OBJECT-TYPE
      SYNTAX      INTEGER {
        tripledes(1),
        blowfish(2),
        aes-cbc(3),
        cast(4),
        arcfour(5),
        aes-ctr(6),
        aes-gcm(7),
        chacha20-poly1305(8)
      }
      MAX-ACCESS  read-write
      STATUS      current
      DESCRIPTION
              "Select the first priority negotiation for the encryption
               method (ciphers) that the Device Server will use for
               the SSH version 2 connection:
               3DES, Blowfish, AES-CBC, CAST, Arcfour,
               AES-CTR, AES-GCM, or ChaCha20-Poly1305"
      ::= { userSessionEntry 30}

  userSessionSSHSecondSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the second priority negotiation for the encryption
               method (ciphers) that the Device Server will use for
               the SSH version 2 connection:
               None, 3DES, Blowfish, AES-CBC, CAST, Arcfour,
               AES-CTR, AES-GCM, or ChaCha20-Poly1305"
      ::= { userSessionEntry 31}

  userSessionSSHThirdSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the third priority negotiation for the encryption
               method (ciphers) that the Device Server will use for
               the SSH version 2 connection:
               None, 3DES, Blowfish, AES-CBC, CAST, Arcfour,
               AES-CTR, AES-GCM, or ChaCha20-Poly1305"
      ::= { userSessionEntry 32}

  userSessionSSHFourthSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the fourth priority negotiation for the encryption
               method (ciphers) that the Device Server will use for
               the SSH version 2 connection:
               None, 3DES, Blowfish, AES-CBC, CAST, Arcfour,
               AES-CTR, AES-GCM, or ChaCha20-Poly1305"
      ::= { userSessionEntry 33}

  userSessionSSHFifthSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the fifth priority negotiation for the encryption
               method (ciphers) that the Device Server will use for
               the SSH version 2 connection:
               None, 3DES, Blowfish, AES-CBC, CAST, Arcfour,
               AES-CTR, AES-GCM, or ChaCha20-Poly1305"
      ::= { userSessionEntry 34}

  userSessionRloginHost OBJECT-TYPE
      SYNTAX      DisplayString(SIZE(0..14))
      MAX-ACCESS  read-write
      STATUS      current
      DESCRIPTION
              "The name of the target host."
      ::= { userSessionEntry 35}

  userSessionRloginTermType OBJECT-TYPE
      SYNTAX      DisplayString(SIZE(0..14))
      MAX-ACCESS  read-write
      STATUS      current
      DESCRIPTION
              "Type of terminal attached to this line; for example, ansi or wyse60."
      ::= { userSessionEntry 36}

  userSessionTelnetTunnelName OBJECT-TYPE
      SYNTAX      DisplayString(SIZE(0..14))
      MAX-ACCESS  read-write
      STATUS      current
      DESCRIPTION
              "The name of the HTTP tunnel associated with the Telnet service."
      ::= { userSessionEntry 37 }
      
  userSessionSSHTunnelName OBJECT-TYPE
      SYNTAX      DisplayString(SIZE(0..14))
      MAX-ACCESS  read-write
      STATUS      current
      DESCRIPTION
              "The name of the HTTP tunnel associated with the SSH service."
      ::= { userSessionEntry 38 }

  userSessionRloginTunnelName OBJECT-TYPE
      SYNTAX      DisplayString(SIZE(0..14))
      MAX-ACCESS  read-write
      STATUS      current
      DESCRIPTION
              "The name of the HTTP tunnel associated with the Rlogin service."
      ::= { userSessionEntry 39 }
  
  userSessionStrictHostKeyChecking  OBJECT-TYPE
      SYNTAX      OnOffValue
      MAX-ACCESS  read-write
      STATUS      current
      DESCRIPTION
              "When set, the device server must have a host key loaded."
      ::= { userSessionEntry 40}
  
  userSessionSSHSixthSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the sixth priority negotiation for the encryption
               method (ciphers) that the Device Server will use for
               the SSH version 2 connection:
               None, 3DES, Blowfish, AES-CBC, CAST, Arcfour,
               AES-CTR, AES-GCM, or ChaCha20-Poly1305"
      ::= { userSessionEntry 41}

  userSessionSSHSeventhSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the seventh priority negotiation for the encryption
               method (ciphers) that the Device Server will use for
               the SSH version 2 connection:
               None, 3DES, Blowfish, AES-CBC, CAST, Arcfour,
               AES-CTR, AES-GCM, or ChaCha20-Poly1305"
      ::= { userSessionEntry 42}

  userSessionSSHEighthSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the eighth priority negotiation for the encryption
               method (ciphers) that the Device Server will use for
               the SSH version 2 connection:
               None, 3DES, Blowfish, AES-CBC, CAST, Arcfour,
               AES-CTR, AES-GCM, or ChaCha20-Poly1305"
      ::= { userSessionEntry 43}

--******************************************************************************  
--  portInfo group. A table of entries, each entry per port.

  portTable OBJECT-TYPE
      SYNTAX      SEQUENCE OF PortEntry
      MAX-ACCESS  not-accessible
      STATUS      current
      DESCRIPTION
              "The port configuration table."
      ::= { portInfo 1 }

  portEntry OBJECT-TYPE
      SYNTAX      PortEntry
      MAX-ACCESS  not-accessible
      STATUS      current
      DESCRIPTION
              "An entry in the port configuration table, each relating to a serial port."
      INDEX   { portIndex }
      ::= { portTable 1 }

  PortEntry ::=
      SEQUENCE {
          portIndex                 PortNumber,
          portStatus                ContainerStatus,
          portName                  DisplayString,
          portService               INTEGER,
          portDial                  INTEGER,
          portModem                 DisplayString,
          portPhone                 DisplayString,
          portTermType              INTEGER,
          portPages                 Integer32,
          portPreDefinedUser        DisplayString,
          portDSPort                Integer32,
          portIdleTimer             Integer32,
          portSessionTimer          Integer32,
          portSecurity              OnOffValue,
          portBreak                 INTEGER,
          portInboundFlowControl    OnOffValue,
          portOutboundFlowControl   OnOffValue,
          portInitialMode           INTEGER,
          portReset                 OnOffValue,
          portKeepalive             OnOffValue,
          portMapCR                 OnOffValue,
          portMOTD                  OnOffValue,
          portHotKeyPrefix          Hex8,
          portLock                  OnOffValue,
          portEnable                OnOffValue,
          portMultiSession          Integer32,
          portDialRetries           Integer32,
          portDialTimeout           Integer32,
          portInternetAddress       Ipv4v6Address,
          portRawOption             INTEGER,
          portDirectTrigger         Hex8,
          portDataLogging           OnOffValue,
          portSacSupport            OnOffValue,
          portSendName              OnOffValue,
          portConnectInitiateString DisplayString,
          portConnectTerminateString DisplayString,
          portConnectStringDelay    Integer32,
          portBreakLength           Integer32,
          portBreakDelay            Integer32
        }

  portIndex OBJECT-TYPE
      SYNTAX      PortNumber
      MAX-ACCESS  not-accessible
      STATUS      current
      DESCRIPTION
              "Serial Port Index. Valid values are 1 to maximum port number the 
               Device Server supports"
      ::= { portEntry 1}

  portStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portEntry 2}

  portName OBJECT-TYPE
      SYNTAX      DisplayString(SIZE(0..30))
      MAX-ACCESS  read-write
      STATUS      current
      DESCRIPTION
              "Provide a name for the line so it can be easily identified."
      ::= { portEntry 3}

  portService OBJECT-TYPE
      SYNTAX      INTEGER {
        dslogin(1),
        directraw(2),
        silentraw(3),
        reverseraw(4),
        bidirectionalmodem(5),
        directtelnet(6),
        silenttelnet(7),
        reversetelnet(8),
        directssh(9),
        silentssh(10),
        reversessh(11),
        directrlogin(12),
        silentrlogin(13),
        slip(14),
        ppp(15),
        printer(16),
        udp(17),
        vmodem(18),
        clienttunnel(19),
        servertunnel(20),
        modbusslave(21),
        modbusmaster(22)
        ,
        customapp(23) 
        ,
        signalIo(24)
        ,
        trueport(25)
        ,
        powermanagement(26)
        
     }
      MAX-ACCESS  read-write
      STATUS      current
      DESCRIPTION
              "Defines the Line Service, which determines how the
               line will be used.  USB ports can only be configured to
               reverseraw(4),reversessh(11),,reversetelnet(8),
               bidirectionalmodem(5), trueport(25),customapp(23)"
      ::= { portEntry 4}

  portDial OBJECT-TYPE
      SYNTAX      INTEGER{
        none(1),
        in(2),
        out(3),
        both(4)
      }
      MAX-ACCESS  read-write
      STATUS      current
      DESCRIPTION
              "Determines how a modem will work on the line. If your user
               is remote and will be dialing in via modem or ISDN TA, set
               this parameter to In; if the Device Server is being used as
               a router, set this parameter to either In, Out, or Both,
               depending on which end of the link your Device Server is
               situated and how you want to initiate the communication."
      ::= { portEntry 5}

  portModem OBJECT-TYPE
      SYNTAX      DisplayString(SIZE(0..20))
      MAX-ACCESS  read-write
      STATUS      current
      DESCRIPTION
              "The name of the predefined modem that is used on this line."
      ::= { portEntry 6}
      
  portPhone OBJECT-TYPE
      SYNTAX      DisplayString(SIZE(0..32))
      MAX-ACCESS  read-write
      STATUS      current
      DESCRIPTION
              "The phone number to use when Dial is set to Out."
      ::= { portEntry 7}

  portTermType OBJECT-TYPE
      SYNTAX      INTEGER {
        wyse60(1),
        vt100(2),
        ansi(3),
        dumb(4),
        tvi925(5),
        ibm3151(6),
        vt320(7),
        hp700(8),
        extra1(9),
        extra2(10),
        extra3(11)
      }
      MAX-ACCESS  read-write
      STATUS      current
      DESCRIPTION
        "Specifies the type of terminal connected to the line:
        Dumb, WYSE60, VT100, ANSI, TVI925, IBM3151TE,
        VT320 (specifically supporting VT320-7),
        HP700 (specifically supporting HP700/44),
        Term1, Term2, Term3 (user defined terminals)"
      ::= { portEntry 8}

  portPages OBJECT-TYPE
      SYNTAX      Integer32(1..7)
      MAX-ACCESS  read-write
      STATUS      current
      DESCRIPTION
              "For DSLogin line service, this is the number of video
               pages the terminal supports. Valid values are 1-7.
               The default is 5 pages."
      ::= { portEntry 9}

  portPreDefinedUser OBJECT-TYPE
      SYNTAX      DisplayString(SIZE(0..16))
      MAX-ACCESS  read-write
      STATUS      current
      DESCRIPTION
              "For DSLogin line service, makes this a line that is dedicated
               to the specified user. Only this user will be able to log in
               on this line and they won't need to enter their login
               name - just their password."
      ::= { portEntry 10}

  portDSPort OBJECT-TYPE
      SYNTAX      Integer32(0..65535)
      MAX-ACCESS  read-write
      STATUS      current
      DESCRIPTION
              "The Device Server port number."
      ::= { portEntry 11}

  portIdleTimer OBJECT-TYPE
      SYNTAX      Integer32(0..4294967)
      MAX-ACCESS  read-write
      STATUS      current
      DESCRIPTION
              "Enter a time period, in seconds, for which the Idle Timer will run.
               Use this timer to close a connection because of inactivity. When the
               Idle Timer expires, the Device Server will end the connection. The
               maximum value is 4294967 seconds (about 49 days). The default value
               of 0 (zero) means the Idle Timer will not expire, so the connection is
               permanently open."
      ::= { portEntry 12}

  portSessionTimer OBJECT-TYPE
      SYNTAX      Integer32(0..4294967)
      MAX-ACCESS  read-write
      STATUS      current
      DESCRIPTION
              "Enter a time, in seconds, for which the Session Timer will run. Use this
               timer to forcibly close the session (connection). When the Session Timer
               expires, the Device Server will end the connection. The default value is
               0 seconds so the port will never timeout. The maximum value is 4294967
               seconds (about 49 days)."
      ::= { portEntry 13}

  portSecurity OBJECT-TYPE
      SYNTAX      OnOffValue
      MAX-ACCESS  read-write
      STATUS      current
      DESCRIPTION
              "Enables/disables login/password authentication, locally or externally,
               on reverse Telnet connections. The default is Off."
      ::= { portEntry 14}

  portBreak OBJECT-TYPE
      SYNTAX      INTEGER {
        off(1),
        local(2),
        remote(3),
        brkintr(4)
      }
      MAX-ACCESS  read-write
      STATUS      current
      DESCRIPTION
              "Specifies how a break is interpreted:
               None-The Device Server ignores the break key completely and
                  it is not passed through to the host. This is the default setting.
               Local-The Device Server deals with the break locally. If the user is
                  in a session, the break key has the same effect as a hot key.
               Remote-When the break key is pressed, the Device Server translates this
                  into a telnet break signal which it sends to the host machine.
               Brkintr-On some systems such as SunOS, XENIX, and AIX, a break received
                  from the peripheral is not passed to the client properly. If the
                  client wishes to make the break act like an interrupt key (for example,
                  when the stty options -ignbrk and brkintr are set)"
      ::= { portEntry 15}

  portInboundFlowControl OBJECT-TYPE
      SYNTAX      OnOffValue
      MAX-ACCESS  read-write
      STATUS      current
      DESCRIPTION
              "Determines if input flow control is to be used.
               Default is On. This is active only when Line Flow Control
               is set to Soft, Hard, or Both."
      ::= { portEntry 16}

  portOutboundFlowControl OBJECT-TYPE
      SYNTAX      OnOffValue
      MAX-ACCESS  read-write
      STATUS      current
      DESCRIPTION
              "Determines if output flow control is to be used.
               Default is On. This is active only when Line Flow Control
               is set to Soft, Hard, or Both."
      ::= { portEntry 17}

  portInitialMode OBJECT-TYPE
      SYNTAX      INTEGER {
        cli(1),
        menu(2)
      }
      MAX-ACCESS  read-write
      STATUS      current
      DESCRIPTION
              "Specifies the initial interface a user navigates when logging
               into the line; either the Menu or a prompt for the CLI.
               The default is CLI."
      ::= { portEntry 18}

  portReset OBJECT-TYPE
      SYNTAX      OnOffValue
      MAX-ACCESS  read-write
      STATUS      current
      DESCRIPTION
              "Resets the terminal type connected to the line when a user logs out."
      ::= { portEntry 19}

  portKeepalive OBJECT-TYPE
      SYNTAX      OnOffValue
      MAX-ACCESS  read-write
      STATUS      current
      DESCRIPTION
              "Enables a per-connection TCP keepalive feature; after approximately
               3 minutes of network connection idle time, the connection will send
               a gratuitous ACK to the network peer, either ensuring the connection
               stays active OR causing a dropped connection condition to be recognized
               by the reverse raw service.
               Applications using this feature need to be aware that there might be
               some considerable delay between a network disconnection and the port
               being available for the next connection attempt; this is to allow any
               data sent on prior connections to be transmitted out of the serial
               port buffer. Application network retry logic needs to accommodate this feature."
      ::= { portEntry 20}

  portMapCR OBJECT-TYPE
      SYNTAX      OnOffValue
      MAX-ACCESS  read-write
      STATUS      current
      DESCRIPTION
              "Maps carriage returns (CR) to carriage return line feed (CRLF).
               The default value is Off."
      ::= { portEntry 21}

  portMOTD OBJECT-TYPE
      SYNTAX      OnOffValue
      MAX-ACCESS  read-write
      STATUS      current
      DESCRIPTION
              "Enables/disables the message of the day on the line."
      ::= { portEntry 22}

  portHotKeyPrefix OBJECT-TYPE
      SYNTAX      Hex8
      MAX-ACCESS  read-write
      STATUS      current
      DESCRIPTION
              "The prefix that a user types to lock a line or redraw the Menu. The
               default value is hex 01, which corresponds to Ctrl-a (^a) (hex value
               02 would be Ctrl-b (^b), etc.):
               ^a l-(Lowercase L) Locks the line until the user unlocks it. The user
                  is prompted for a password (any password, excluding spaces) and locks
                  the line. Next, the user must retype the password to unlock the line.
               ^r-When you switch from a session back to the Menu, the screen may not
                  be redrawn correctly. If this happens, use this command to redraw it properly.
               You can use the Hotkey Prefix key to lock a line only when the Line
               Lock parameter is On."
      ::= { portEntry 23}

  portLock OBJECT-TYPE
      SYNTAX      OnOffValue
      MAX-ACCESS  read-write
      STATUS      current
      DESCRIPTION
              "When enabled, the user can lock his terminal with a password using the
               Hotkey Prefix (default Ctrl-a) ^a l (lowercase L). The Device Server
               prompts the user for a password and a confirmation."
      ::= { portEntry 24}

   portEnable OBJECT-TYPE
      SYNTAX      OnOffValue
      MAX-ACCESS  read-write
      STATUS      current
      DESCRIPTION
              "Is the Port Enabled. This field is not available on 1-port units."
      ::= { portEntry 25}
   portMultiSession OBJECT-TYPE
      SYNTAX      Integer32(0..255)
      MAX-ACCESS  read-write
      STATUS      current
      DESCRIPTION
              "The number of Multisessions allowed on this port"
      ::= { portEntry 26}

   portDialRetries OBJECT-TYPE
      SYNTAX      Integer32(0..99)
      MAX-ACCESS  read-write
      STATUS      current
      DESCRIPTION
              "The number of Dial Retries."
      ::= { portEntry 27}

   portDialTimeout OBJECT-TYPE
      SYNTAX      Integer32(1..99)
      MAX-ACCESS  read-write
      STATUS      current
      DESCRIPTION
              "The timeout value when dialing in seconds."
      ::= { portEntry 28}

   portInternetAddress OBJECT-TYPE
      SYNTAX      Ipv4v6Address
      MAX-ACCESS  read-write
      STATUS      current
      DESCRIPTION
              "The Internet address of this port."
      ::= { portEntry 29}
      
	portRawOption OBJECT-TYPE
      SYNTAX      INTEGER {
        noneMultihost(1),
        multihost(2),
        directAny(3)
     }
      MAX-ACCESS  read-write
      STATUS      current
      DESCRIPTION
              "Defines the multihost Service and direct connection initiate mode"
      ::= { portEntry 30}

	portDirectTrigger OBJECT-TYPE
	 SYNTAX	 Hex8
      MAX-ACCESS  read-write
      STATUS      current
      DESCRIPTION
              "Defines the direct connection initiate char"
      ::= { portEntry 31}

   portDataLogging OBJECT-TYPE
      SYNTAX      OnOffValue
      MAX-ACCESS  read-write
      STATUS      current
      DESCRIPTION
              "When on, serial data will be buffered if the TCP connection is lost. 
               When the TCP connection is re-established, the buffered serial data will 
               be sent to its destination (this option is not available when Monitor DSR, 
               Monitor DCD, or Multihost is enabled). 
               The data buffer is 4K for desktop models and 32K for rack mount models. 
               If the data buffer is filled, incoming serial data will overwrite the 
               oldest data. The default is off."
      ::= { portEntry 32}

   portSacSupport OBJECT-TYPE
      SYNTAX      OnOffValue
      MAX-ACCESS  read-write
      STATUS      current
      DESCRIPTION
		  		"When on, a user can access SAC (the interface of the Microsoft 
				 Emergency Management Systems utility) through EasyPort Web when the device server's 
				 serial port is connected to a Microsoft Server 2003 or 
				 Microsoft Server 2008 host. The default is off."
      ::= { portEntry 33}
  
   portSendName OBJECT-TYPE
      SYNTAX      OnOffValue
      MAX-ACCESS  read-write
      STATUS      current
      DESCRIPTION
                "Send the port name on connect.  Applies to direct raw, silent raw,
                and TruePort (server-initiated) srevice types."
      ::= { portEntry 34}

  portConnectInitiateString OBJECT-TYPE
      SYNTAX      DisplayString(SIZE(0..127))
      MAX-ACCESS  read-write
      STATUS      current
      DESCRIPTION
                "String to be sent when connection is initiated."
      ::= { portEntry 35}

  portConnectTerminateString OBJECT-TYPE
      SYNTAX      DisplayString(SIZE(0..127))
      MAX-ACCESS  read-write
      STATUS      current
      DESCRIPTION
                "String to be sent when connection is terminated."
      ::= { portEntry 36}
      
  portConnectStringDelay OBJECT-TYPE
      SYNTAX      Integer32(0..65535)
      MAX-ACCESS  read-write
      STATUS      current
      DESCRIPTION
              "The delay after sending the connect or terminate string, in milliseconds"
      ::= { portEntry 37}
      
  portBreakLength OBJECT-TYPE
      SYNTAX      Integer32(0..65535)
      MAX-ACCESS  read-write
      STATUS      current
      DESCRIPTION
              "Amount of time, in milliseconds, to send a break signal (tunnel service only)"
      ::= { portEntry 38}

  portBreakDelay OBJECT-TYPE
      SYNTAX      Integer32(0..65535)
      MAX-ACCESS  read-write
      STATUS      current
      DESCRIPTION
              "The delay, in milliseconds, after sending a break signal (tunnel service only)"
      ::= { portEntry 39}
      
-- port Hdw Table

  portHdwTable OBJECT-TYPE
      SYNTAX      SEQUENCE OF PortHdwEntry
      MAX-ACCESS  not-accessible
      STATUS      current
      DESCRIPTION
              "Port."
      ::= { portInfo 2 }

  portHdwEntry OBJECT-TYPE
      SYNTAX      PortHdwEntry
      MAX-ACCESS  not-accessible
      STATUS      current
      DESCRIPTION
              "An entry in the portHdwEntry, each relating to a port."
      INDEX   { portHdwIndex }
      ::= { portHdwTable 1 }

  PortHdwEntry ::=
      SEQUENCE {
        portHdwIndex             PortNumber,
        portHdwStatus            ContainerStatus,
        portHdwInterface         INTEGER,
        portHdwSpeed             INTEGER,
        portHdwDataBits          INTEGER,
        portHdwParity            INTEGER,
        portHdwStopBits          INTEGER,
        portHdwFlowControl       INTEGER,
        portHdwMonitorDSR        OnOffValue,
        portHdwMonitorDCD        OnOffValue,
        portHdwDuplex            INTEGER,
        portHdwTXDriverControl   INTEGER,
        portHdwEchoSuppression   OnOffValue,
        portHdwUART              INTEGER,
        portHdwIRQ               Integer32,
        portHdwTxBytes           Counter32,
        portHdwRxBytes           Counter32,
        portHdwFrameErrs         Counter32,
        portHdwParityErrs        Counter32,
        portHdwBreaks            Counter32,
        portHdwOverruns          Counter32,
        portHdwRTS               OnOffValue,
        portHdwCTS               OnOffValue,
        portHdwDTR               OnOffValue,
        portHdwDSR               OnOffValue,
        portHdwCD                OnOffValue,
        portHdwRI                OnOffValue,

        portSoftTermination      OnOffValue,
        portHdwCustomSpeed       Integer32, 
        portHdwDiscardCharactersRecievedWithErrors		OnOffValue,
        portHdwRtsToggle         OnOffValue,
        portHdwRtsInitialDelay   Integer32,
        portHdwRtsFinalDelay     Integer32,
		portHdwDataEquipment     Integer,
		portHdwSlot              Integer
        }
  portHdwIndex OBJECT-TYPE
      SYNTAX      PortNumber
      MAX-ACCESS  not-accessible
      STATUS      current
      DESCRIPTION
              "Port hardware Index"
      ::= { portHdwEntry 1 }

  portHdwStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portHdwEntry 2}

  portHdwInterface OBJECT-TYPE
      SYNTAX      INTEGER {
        eia232(1),
        eia422(2),
        eia485(3)
      }
      MAX-ACCESS  read-write
      STATUS      current
      DESCRIPTION
              "Specifies the type of line that is being used with the
               Device Server. Select either EIA-232, EIA-422, or EIA-485."
      ::= { portHdwEntry 3}

  portHdwSpeed OBJECT-TYPE
      SYNTAX      INTEGER {
        b50(1),
        b75(2),
        b110(3),
        b134(4),
        b150(5),
        b200(6),
        b300(7),
        b600(8),
        b1200(9),
        b1800(10),
        b2400(11),
        b4800(12),
        b9600(13),
        b19200(14),
        b38400(15),
        b57600(16),
        b115200(17),
        b230400(18),
        b28800(23),
        bCustom(24)
      }
      MAX-ACCESS  read-write
      STATUS      current
      DESCRIPTION
              "Specifies the baud rate of the line; keep in mind that
               speed is affected by the length of the cable.  When bCustom
               is set, then the baud rate is specified by portHwdCustomSpeed.
               Internal modems only support the following baud rates:
               300, 1200, 2400, 4800, 9600, 19200, 38400, 57600, 
               115200, and 28800."
      ::= { portHdwEntry 4}

  portHdwDataBits OBJECT-TYPE
      SYNTAX      INTEGER {
        d5(1),
        d6(2),
        d7(3),
        d8(4)
      }
      MAX-ACCESS  read-write
      STATUS      current
      DESCRIPTION
              "Specifies the number of bits in a byte. The default is 8.
               Internal modems only support 7 and 8 data bits."
      ::= { portHdwEntry 5}

  portHdwParity OBJECT-TYPE
      SYNTAX      INTEGER {
        none(1),
        odd(2),
        even(3),
        mark(4),
        space(5)
      }
      MAX-ACCESS  read-write
      STATUS      current
      DESCRIPTION
              "Specifies if you are using Even, Odd, or No parity on the line.
               If you want to force a parity type, you can specify Mark for 1
               or Space for 0. "
      ::= { portHdwEntry 6}

  portHdwStopBits OBJECT-TYPE
      SYNTAX      INTEGER {
        s1(1),
        s2(2),
        s1d5(3)
      }
      MAX-ACCESS  read-write
      STATUS      current
      DESCRIPTION
              "Specifies the number of stop bits that follow a byte. 
               Certain models do not support 1.5 stop bits. Internal 
               modems only support 1 stop bit."
      ::= { portHdwEntry 7}

  portHdwFlowControl OBJECT-TYPE
      SYNTAX      INTEGER {
        none(1),
        soft(2),
        hard(3),
        both(4)
      }
      MAX-ACCESS  read-write
      STATUS      current
      DESCRIPTION
              "Defines whether the data flow is handled by the
               software (Soft), hardware (Hard), Both, or None."
      ::= { portHdwEntry 8}

  portHdwMonitorDSR OBJECT-TYPE
      SYNTAX      OnOffValue
      MAX-ACCESS  read-write
      STATUS      current
      DESCRIPTION
              "Specifies whether the RS-232 signal DSR (Data Set Ready) should
               be monitored, for Device Servers with a DTE serial interface.
               On a Device Server with a DCE serial interface, this object 
               specifies whether the DTR (Data Terminal Ready) signal should
               be monitored.
               
               For DTE interfaces, this is used with modems or any device that sends
               a DSR signal. When it is monitored and the Device Server detects
               a DSR signal, the line service is started. Default is Off. If
               both Monitor DCD and Monitor DSR are enabled, both signals must
               be detected before the line service is started.
               
               For DCE interfaces, this is used with terminals or other devices
               that output a DTR signal.
               
               This value cannot be changed for internal modems."
      ::= { portHdwEntry 9}

  portHdwMonitorDCD OBJECT-TYPE
      SYNTAX      OnOffValue
      MAX-ACCESS  read-write
      STATUS      current
      DESCRIPTION
              "Specifies whether the RS-232 signal DCD (Data Carrier Detect) should
               be monitored.  This object does not apply to DCE serial interfaces.
               
               This is used with modems or any other device that sends
               a DCD signal. When it is monitored and the Device Server detects a
               DCD signal, the line service is started. Default is Off. If both
               Monitor DCD and Monitor DSR are enabled, both signals must be detected
               before the line service is started."
      ::= { portHdwEntry 10}

  portHdwDuplex OBJECT-TYPE
      SYNTAX      INTEGER {
        half(1),
        full(2)
      }
      MAX-ACCESS  read-write
      STATUS      current
      DESCRIPTION
              "Specify whether the line is Full Duplex (communication both ways
               at the same time) or Half Duplex (communication in one direction
               at a time)."
      ::= { portHdwEntry 11}

  portHdwTXDriverControl OBJECT-TYPE
      SYNTAX      INTEGER {
        auto(1),
        rts(2)
      }
      MAX-ACCESS  read-write
      STATUS      current
      DESCRIPTION
              "Used with a EIA-485 serial interface, if your application supports
               RTS (Request To Send), select this option. Otherwise, select Auto.
               Default is Auto"
      ::= { portHdwEntry 12}

  portHdwEchoSuppression OBJECT-TYPE
      SYNTAX      OnOffValue
      MAX-ACCESS  read-write
      STATUS      current
      DESCRIPTION
              "This parameter applies only to EIA-485 Half Duplex mode. All characters
               will be echoed to the user and transmitted across the serial ports.
               Some EIA-485 applications require local echo to be enabled in order to
               monitor the loopback data to determine that line contention has occurred.
               If your application cannot handle loopback data, echo suppression should
               be On. The default is echo suppression Off."
      ::= { portHdwEntry 13}

  portHdwUART OBJECT-TYPE
      SYNTAX      INTEGER {
        scc(1),
        smc(2),
        exar(3)
      }
      MAX-ACCESS  read-only
      STATUS      current
      DESCRIPTION
              "portHdwUART"
      ::= { portHdwEntry 14}

  portHdwIRQ OBJECT-TYPE
      SYNTAX      Integer32(0..255)
      MAX-ACCESS  read-only
      STATUS      current
      DESCRIPTION
              "Port Hardware IRQ"
      ::= { portHdwEntry 15}

  portHdwTxBytes OBJECT-TYPE
      SYNTAX      Counter32
      MAX-ACCESS  read-only
      STATUS      current
      DESCRIPTION
              "portHdwTxBytes"
      ::= { portHdwEntry 16}

  portHdwRxBytes OBJECT-TYPE
      SYNTAX      Counter32
      MAX-ACCESS  read-only
      STATUS      current
      DESCRIPTION
              "portHdwRxBytes"
      ::= { portHdwEntry 17}

  portHdwFrameErrs OBJECT-TYPE
      SYNTAX      Counter32
      MAX-ACCESS  read-only
      STATUS      current
      DESCRIPTION
              "portHdwFrameErrs"
      ::= { portHdwEntry 18}

  portHdwParityErrs OBJECT-TYPE
      SYNTAX      Counter32
      MAX-ACCESS  read-only
      STATUS      current
      DESCRIPTION
              "portHdwParityErrs"
      ::= { portHdwEntry 19}

  portHdwBreaks OBJECT-TYPE
      SYNTAX      Counter32
      MAX-ACCESS  read-only
      STATUS      current
      DESCRIPTION
              "portHdwBreaks"
      ::= { portHdwEntry 20}

  portHdwOverruns OBJECT-TYPE
      SYNTAX      Counter32
      MAX-ACCESS  read-only
      STATUS      current
      DESCRIPTION
              "portHdwOverruns"
      ::= { portHdwEntry 21}

  portHdwRTS OBJECT-TYPE
      SYNTAX      OnOffValue
      MAX-ACCESS  read-only
      STATUS      current
      DESCRIPTION
              "portHdwRTS"
      ::= { portHdwEntry 22}

  portHdwCTS OBJECT-TYPE
      SYNTAX      OnOffValue
      MAX-ACCESS  read-only
      STATUS      current
      DESCRIPTION
              "portHdwCTS"
      ::= { portHdwEntry 23}

  portHdwDTR OBJECT-TYPE
      SYNTAX      OnOffValue
      MAX-ACCESS  read-only
      STATUS      current
      DESCRIPTION
              "portHdwDTR"
      ::= { portHdwEntry 24}

  portHdwDSR OBJECT-TYPE
      SYNTAX      OnOffValue
      MAX-ACCESS  read-only
      STATUS      current
      DESCRIPTION
              "portHdwDSR"
      ::= { portHdwEntry 25}

  portHdwCD OBJECT-TYPE
      SYNTAX      OnOffValue
      MAX-ACCESS  read-only
      STATUS      current
      DESCRIPTION
              "portHdwCD"
      ::= { portHdwEntry 26}

  portHdwRI OBJECT-TYPE
      SYNTAX      OnOffValue
      MAX-ACCESS  read-only
      STATUS      current
      DESCRIPTION
              "portHdwRI"
      ::= { portHdwEntry 27}

  
 portSoftTermination OBJECT-TYPE
      SYNTAX      OnOffValue
      MAX-ACCESS  read-write
      STATUS      current
      DESCRIPTION
              "Enables or disables software line termination."
      ::= { portHdwEntry 29}
      
   portHdwCustomSpeed OBJECT-TYPE
      SYNTAX      Integer32(50..1843200)
      MAX-ACCESS  read-write
      STATUS      current
      DESCRIPTION
              "The custom baud rate for this port."
      ::= { portHdwEntry 30 }
      
  portHdwDiscardCharactersRecievedWithErrors	OBJECT-TYPE
      SYNTAX      OnOffValue
      MAX-ACCESS  read-write
      STATUS      current
      DESCRIPTION
              "This option if set will discard any characters recieved on the 
               uart that have overrun, framing or parity errors. If not set, 
               then the characters are sent out the network connection"
      ::= { portHdwEntry 31}
      
  portHdwRtsToggle	OBJECT-TYPE
      SYNTAX      OnOffValue
      MAX-ACCESS  read-write
      STATUS      current
      DESCRIPTION
              "This option if set will toggle RTS on before transmitting the
               first character and toggle RTS off after transmitting the 
               last character."
      ::= { portHdwEntry 32}
      
  portHdwRtsInitialDelay OBJECT-TYPE
      SYNTAX      Integer32(0..1000)
      MAX-ACCESS  read-write
      STATUS      current
      DESCRIPTION
              "The delay, in msec, between turning RTS on and transmittng 
               the first character."
      ::= { portHdwEntry 33}

  portHdwRtsFinalDelay OBJECT-TYPE
      SYNTAX      Integer32(0..1000)
      MAX-ACCESS  read-write
      STATUS      current
      DESCRIPTION
              "The delay, in msec, between transmitting the last character
               and turning RTS off."
      ::= { portHdwEntry 34}

  portHdwDataEquipment OBJECT-TYPE
      SYNTAX      Integer{Rolled (1) , Straight (2)}
      MAX-ACCESS  read-write
      STATUS      current
      DESCRIPTION
              "This option if set will toggle between Data Terminal Equipment (DTE) Rolled and 
               Data Communication Equipment (DCE) Straight."
      ::= { portHdwEntry 35}   

  portHdwSlot OBJECT-TYPE
      SYNTAX        Integer{Disabled (1) , USB (2), RS232 (3)}
      MAX-ACCESS    read-only
      STATUS        current
	  DESCRIPTION
	            "Slot hardware available. 
				portHdwSlot.1 (ports 1 - 16)
				portHdwSlot.2 (ports 17- 32)
                portHdwSlot.3 (ports 33- 48)"
	  ::= { portHdwEntry 36}	  
--******************************************************************************  
--- Port Telnet Table

  portTelnetTable OBJECT-TYPE
      SYNTAX      SEQUENCE OF PortTelnetEntry
      MAX-ACCESS  not-accessible
      STATUS      current
      DESCRIPTION
              "Port Telnet Table."
      ::= { portInfo 3 }

  portTelnetEntry OBJECT-TYPE
      SYNTAX      PortTelnetEntry
      MAX-ACCESS  not-accessible
      STATUS      current
      DESCRIPTION
              "An entry in the portTelnetEntry, each relating to a port."
      INDEX   { portTelnetIndex }
      ::= { portTelnetTable 1 }

  PortTelnetEntry ::=
      SEQUENCE {
          portTelnetIndex            PortNumber,
          portTelnetStatus            ContainerStatus,
          portTelnetPort            Integer32,
          portTelnetHost            DisplayString,
          portTelnetTermType            DisplayString,
          portTelnetEcho            OnOffValue,
          portTelnetMapnl            OnOffValue,
          portTelnetMode            OnOffValue,
          portTelnetInterrupt            Hex8,
          portTelnetQuit            Hex8,
          portTelnetEOF            Hex8,
          portTelnetErase            Hex8,
          portTelnetEchoCC            Hex8,
          portTelnetBreak            Hex8,
          portTelnetTunnelName      DisplayString
      }
  portTelnetIndex OBJECT-TYPE
      SYNTAX      PortNumber
      MAX-ACCESS  not-accessible
      STATUS      current
      DESCRIPTION
              "portTelnetIndex"
      ::= { portTelnetEntry 1 }

  portTelnetStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portTelnetEntry 2}

  portTelnetPort OBJECT-TYPE
      SYNTAX      Integer32(0..65535)
      MAX-ACCESS  read-write
      STATUS      current
      DESCRIPTION
              "The port number the target host is listening on for
               incoming connections. Default is 23."
      ::= { portTelnetEntry 3 }

  portTelnetHost OBJECT-TYPE
      SYNTAX      DisplayString(SIZE(0..14))
      MAX-ACCESS  read-write
      STATUS      current
      DESCRIPTION
              "The name of the target host."
      ::= { portTelnetEntry 4 }

  portTelnetTermType OBJECT-TYPE
      SYNTAX      DisplayString(SIZE(0..14))
      MAX-ACCESS  read-write
      STATUS      current
      DESCRIPTION
              "Type of terminal attached to this line; for example, ANSI or WYSE60."
      ::= { portTelnetEntry 5 }

  portTelnetEcho OBJECT-TYPE
      SYNTAX      OnOffValue
      MAX-ACCESS  read-write
      STATUS      current
      DESCRIPTION
              "Toggles between local echo of entered characters and suppressing
               local echo. Local echo is used for normal processing, while suppressing
               the echo is convenient for entering text that should not be displayed
               on the screen, such as passwords. This parameter can only be used when
               Line Mode is On. Default is Off."
      ::= { portTelnetEntry 6}

  portTelnetMapnl OBJECT-TYPE
      SYNTAX      OnOffValue
      MAX-ACCESS  read-write
      STATUS      current
      DESCRIPTION
              "Maps carriage returns (CR) to carriage return line feed (CRLF).
               The default value is Off."
      ::= { portTelnetEntry 7 }

  portTelnetMode OBJECT-TYPE
      SYNTAX      OnOffValue
      MAX-ACCESS  read-write
      STATUS      current
      DESCRIPTION
              "When On, keyboard input is not sent to the remote host until
               Enter is pressed, otherwise input is sent every time a key
               is pressed. Default is Off."
      ::= { portTelnetEntry 8}

  portTelnetInterrupt OBJECT-TYPE
      SYNTAX      Hex8
      MAX-ACCESS  read-write
      STATUS      current
      DESCRIPTION
              "Defines the interrupt character. Typing the interrupt
               character interrupts the current process. This value is in
               hexadecimal with a default value of 3 (ASCII value ^C)."
      ::= { portTelnetEntry 9 }

  portTelnetQuit OBJECT-TYPE
      SYNTAX      Hex8
      MAX-ACCESS  read-write
      STATUS      current
      DESCRIPTION
              "Defines the quit character. Typing the quit character closes
               and exits the current telnet session. This value is in
               hexadecimal with a default value of 1c (ASCII value FS)."
      ::= { portTelnetEntry 10}

  portTelnetEOF OBJECT-TYPE
      SYNTAX      Hex8
      MAX-ACCESS  read-write
      STATUS      current
      DESCRIPTION
              "Defines the end-of-file character. When Line Mode is On,
               entering the eof character as the first character on a line
               sends the character to the remote host. This value is in hexadecimal
               with a default value of 4 (ASCII value ^D)."
      ::= { portTelnetEntry 11 }

  portTelnetErase OBJECT-TYPE
      SYNTAX      Hex8
      MAX-ACCESS  read-write
      STATUS      current
      DESCRIPTION
              "Defines the erase character. When Line Mode is Off, typing the erase
               character erases one character. This value is in hexadecimal with a
               default value of 8 (ASCII value ^H)."
      ::= { portTelnetEntry 12 }

  portTelnetEchoCC OBJECT-TYPE
      SYNTAX      Hex8
      MAX-ACCESS  read-write
      STATUS      current
      DESCRIPTION
              "Defines the echo character. When Line Mode is On, typing the echo
               character echoes the text locally and sends only completed lines to
               the host. This value is in hexadecimal with a default value of 5
               (ASCII value ^E)."
      ::= { portTelnetEntry 13 }

  portTelnetBreak OBJECT-TYPE
      SYNTAX      Hex8
      MAX-ACCESS  read-write
      STATUS      current
      DESCRIPTION
              "Defines the escape character. Returns you to the command line mode.
               This value is in hexadecimal with a default value of 1d (ASCII value GS)."
      ::= { portTelnetEntry 14}
  
  portTelnetTunnelName OBJECT-TYPE
      SYNTAX      DisplayString(SIZE(0..14))
      MAX-ACCESS  read-write
      STATUS      current
      DESCRIPTION
              "The name of the HTTP tunnel associated with this service."
      ::= { portTelnetEntry 15 }
  

-- Port SSH Table

  portSSHTable OBJECT-TYPE
      SYNTAX      SEQUENCE OF PortSSHEntry
      MAX-ACCESS  not-accessible
      STATUS      current
      DESCRIPTION
              "Port SSH Table."
      ::= { portInfo 4 }

  portSSHEntry OBJECT-TYPE
      SYNTAX      PortSSHEntry
      MAX-ACCESS  not-accessible
      STATUS      current
      DESCRIPTION
              "An entry in the portSSHEntry, each relating to a port."
      INDEX   { portSSHIndex }
      ::= { portSSHTable 1 }

  PortSSHEntry ::=
      SEQUENCE {
        portSSHIndex            PortNumber,
        portSSHStatus            ContainerStatus,
        portSSHPort            Integer32,
        portSSHHost            DisplayString,
        portSSHTermType            DisplayString,
        portSSHVerbose            OnOffValue,
        portSSHCompression            OnOffValue,
        portSSHAutoLogin            OnOffValue,
        portSSHName            DisplayString,
        portSSHProtocol            INTEGER,
        portSSHRSA            OnOffValue,
        portSSHDSA            OnOffValue,
        portSSHKeyboard            OnOffValue,
        portSSHCipherSSH1            INTEGER,
        portSSHFirstSSH2Cipher            INTEGER,
        portSSHSecondSSH2Cipher            INTEGER,
        portSSHThirdSSH2Cipher            INTEGER,
        portSSHFourthSSH2Cipher            INTEGER,
        portSSHFifthSSH2Cipher            INTEGER,
        portSSHTunnelName        DisplayString,
        portSSHStrictHostKeyChecking OnOffValue,
        portSSHSixthSSH2Cipher            INTEGER,
        portSSHSeventhSSH2Cipher            INTEGER,
        portSSHEighthSSH2Cipher            INTEGER

  }
  portSSHIndex OBJECT-TYPE
      SYNTAX      PortNumber
      MAX-ACCESS  not-accessible
      STATUS      current
      DESCRIPTION
              "portSSHIndex"
      ::= { portSSHEntry 1}

  portSSHStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portSSHEntry 2}

  portSSHPort OBJECT-TYPE
      SYNTAX      Integer32(0..65535)
      MAX-ACCESS  read-write
      STATUS      current
      DESCRIPTION
              "The port number the target host is listening on
               for incoming connections. The default is port 22."
      ::= { portSSHEntry 3}

  portSSHHost OBJECT-TYPE
      SYNTAX      DisplayString(SIZE(0..14))
      MAX-ACCESS  read-write
      STATUS      current
      DESCRIPTION
              "The name of the target host."
      ::= { portSSHEntry 4}

  portSSHTermType OBJECT-TYPE
      SYNTAX      DisplayString(SIZE(0..14))
      MAX-ACCESS  read-write
      STATUS      current
      DESCRIPTION
              "The type of terminal that will connecting via SSH."
      ::= { portSSHEntry 5}

  portSSHVerbose OBJECT-TYPE
      SYNTAX      OnOffValue
      MAX-ACCESS  read-write
      STATUS      current
      DESCRIPTION
              "Displays debug messages on the terminal."
      ::= { portSSHEntry 6}

  portSSHCompression OBJECT-TYPE
      SYNTAX      OnOffValue
      MAX-ACCESS  read-write
      STATUS      current
      DESCRIPTION
              "Requests compression of all data. Compression is desirable
               on modem lines and other slow connections, but will only
               slow down things on fast networks"
      ::= { portSSHEntry 7}

  portSSHAutoLogin OBJECT-TYPE
      SYNTAX      OnOffValue
      MAX-ACCESS  read-write
      STATUS      current
      DESCRIPTION
              "Creates an automatic SSH login, using the Name and Password values."
      ::= { portSSHEntry 8}

  portSSHName OBJECT-TYPE
      SYNTAX      DisplayString(SIZE(0..20))
      MAX-ACCESS  read-write
      STATUS      current
      DESCRIPTION
              "The name of the user logging into the SSH session."
      ::= { portSSHEntry 9}

  portSSHProtocol OBJECT-TYPE
      SYNTAX      INTEGER {
        ssh1(1),
        ssh2(2),
        sshBoth(3)
      }
      MAX-ACCESS  read-write
      STATUS      current
      DESCRIPTION
              "Specify the SSH client version that will be used
               for the SSH session."
      ::= { portSSHEntry 10}

  portSSHRSA OBJECT-TYPE
      SYNTAX      OnOffValue
      MAX-ACCESS  read-write
      STATUS      current
      DESCRIPTION
              "An authentication method used by SSH version 1 and 2.
               Use RSA authentication for the SSH session."
      ::= { portSSHEntry 11}

  portSSHDSA OBJECT-TYPE
      SYNTAX      OnOffValue
      MAX-ACCESS  read-write
      STATUS      current
      DESCRIPTION
              "An authentication method used by SSH version 2.
               Use DSA authentication for the SSH session."
      ::= { portSSHEntry 12}

  portSSHKeyboard OBJECT-TYPE
      SYNTAX      OnOffValue
      MAX-ACCESS  read-write
      STATUS      current
      DESCRIPTION
              "The user types in a password for authentication."
      ::= { portSSHEntry 13}

  portSSHCipherSSH1 OBJECT-TYPE
      SYNTAX      INTEGER {
              tripledes(1),
          blowfish(2)
        }
      MAX-ACCESS  read-write
      STATUS      current
      DESCRIPTION
              "Select the encryption method (cipher) that you
               want to use for your SSH version 1 connection:
               3DES or Blowfish"
      ::= { portSSHEntry 14}

  portSSHFirstSSH2Cipher OBJECT-TYPE
      SYNTAX      INTEGER {
        tripledes(1),
        blowfish(2),
        aes-cbc(3),
        cast(4),
        arcfour(5),
        aes-ctr(6),
        aes-gcm(7),
        chacha20-poly1305(8)
      }
      MAX-ACCESS  read-write
      STATUS      current
      DESCRIPTION
              "Select the first priority negotiation for the encryption
               method (ciphers) that the Device Server will use for
               the SSH version 2 connection:
               3DES, Blowfish, AES-CBC, CAST, Arcfour,
               AES-CTR, AES-GCM, or ChaCha20-Poly1305"
      ::= { portSSHEntry 15}

  portSSHSecondSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the second priority negotiation for the encryption
               method (ciphers) that the Device Server will use for
               the SSH version 2 connection:
               None, 3DES, Blowfish, AES-CBC, CAST, Arcfour,
               AES-CTR, AES-GCM, or ChaCha20-Poly1305"
      ::= { portSSHEntry 16}

  portSSHThirdSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the third priority negotiation for the encryption
               method (ciphers) that the Device Server will use for
               the SSH version 2 connection:
               None, 3DES, Blowfish, AES-CBC, CAST, Arcfour,
               AES-CTR, AES-GCM, or ChaCha20-Poly1305"
      ::= { portSSHEntry 17}

  portSSHFourthSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the fourth priority negotiation for the encryption
               method (ciphers) that the Device Server will use for
               the SSH version 2 connection:
               None, 3DES, Blowfish, AES-CBC, CAST, Arcfour,
               AES-CTR, AES-GCM, or ChaCha20-Poly1305"
      ::= { portSSHEntry 18}

  portSSHFifthSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the fifth priority negotiation for the encryption
               method (ciphers) that the Device Server will use for
               the SSH version 2 connection:
               None, 3DES, Blowfish, AES-CBC, CAST, Arcfour,
               AES-CTR, AES-GCM, or ChaCha20-Poly1305"
      ::= { portSSHEntry 19}
  
  portSSHTunnelName OBJECT-TYPE
      SYNTAX      DisplayString(SIZE(0..14))
      MAX-ACCESS  read-write
      STATUS      current
      DESCRIPTION
              "The name of the HTTP tunnel associated with this service."
      ::= { portSSHEntry 20 }
  
  portSSHStrictHostKeyChecking  OBJECT-TYPE
      SYNTAX      OnOffValue
      MAX-ACCESS  read-write
      STATUS      current
      DESCRIPTION
              "When set, the device server must have a host key loaded."
      ::= { portSSHEntry 21}

  portSSHSixthSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the sixth priority negotiation for the encryption
               method (ciphers) that the Device Server will use for
               the SSH version 2 connection:
               None, 3DES, Blowfish, AES-CBC, CAST, Arcfour,
               AES-CTR, AES-GCM, or ChaCha20-Poly1305"
     ::= { portSSHEntry 22}
  
  portSSHSeventhSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the seventh priority negotiation for the encryption
               method (ciphers) that the Device Server will use for
               the SSH version 2 connection:
               None, 3DES, Blowfish, AES-CBC, CAST, Arcfour,
               AES-CTR, AES-GCM, or ChaCha20-Poly1305"
      ::= { portSSHEntry 23}
  
  portSSHEighthSSH2Cipher OBJECT-TYPE
      SYNTAX      INTEGER {
        none(1),
        tripledes(2),
        blowfish(3),
        aes-cbc(4),
        cast(5),
        arcfour(6),
        aes-ctr(7),
        aes-gcm(8),
        chacha20-poly1305(9)
      }
      MAX-ACCESS  read-write
      STATUS      current
      DESCRIPTION
              "Select the eighth priority negotiation for the encryption
               method (ciphers) that the Device Server will use for
               the SSH version 2 connection:
               None, 3DES, Blowfish, AES-CBC, CAST, Arcfour,
               AES-CTR, AES-GCM, or ChaCha20-Poly1305"
      ::= { portSSHEntry 24}
  
-- Port PPP Table

  portPPPTable OBJECT-TYPE
      SYNTAX      SEQUENCE OF PortPPPEntry
      MAX-ACCESS  not-accessible
      STATUS      current
      DESCRIPTION
              "Port PPP Table."
      ::= { portInfo 5 }

  portPPPEntry OBJECT-TYPE
      SYNTAX      PortPPPEntry
      MAX-ACCESS  not-accessible
      STATUS      current
      DESCRIPTION
              "An entry in the portPPPEntry, each relating to a port."
      INDEX   { portPPPIndex }
      ::= { portPPPTable 1 }

  PortPPPEntry ::=
      SEQUENCE {
        portPPPIndex                   PortNumber,
        portPPPStatus                  ContainerStatus,
        portPPPLocalIpAddr             IpAddress,
        portPPPRemoteIpAddr            IpAddress,
        portPPPSubnetBits              Integer32,
        portPPPIpV6LocalIpAddr         Ipv6InterfaceId,
        portPPPIpV6RemoteIpAddr        Ipv6InterfaceId,
        portPPPAccm                    Hex32,
        portPPPMru                     Integer32,
        portPPPSecurity                INTEGER,
        portPPPUser                    DisplayString,
        portPPPRemoteUser              DisplayString,
        portPPPACComp                  OnOffValue,
        portPPPProtoComp               OnOffValue,
        portPPPVJComp                  OnOffValue,
        portPPPMagicNegotiation        OnOffValue,
        portPPPIPAddrNegotiation       OnOffValue,
        portPPPCRTimeout               Integer32,
        portPPPTRTimeout               Integer32,
        portPPPCRRetry                 Integer32,
        portPPPTRRetry                 Integer32,
        portPPPNakRetry                Integer32,
        portPPPAuthTimeout             Integer32,
        portPPPRoamingCallback         OnOffValue,
        portPPPChallengInterval        Integer32,
        portPPPRouting                 INTEGER,
        portPPPDynamicDNSEnabled       OnOffValue,
        portPPPDynamicDNSHostname      DisplayString,
        portPPPDynamicDNSUserName      DisplayString,
        portPPPDynamicDNSPassword      DisplayString,
        portPPPDynamicDNSStatusString  OCTET STRING,
        portPPPMSDirectConnection      INTEGER,
        portPPPIPv6Prefix              Ipv4v6Address,
        portPPPIPv6PrefixBits          Integer32,
        portPPPEchoTimeout             Integer32,
        portPPPEchoRetry               Integer32
      }
  portPPPIndex OBJECT-TYPE
      SYNTAX      PortNumber
      MAX-ACCESS  not-accessible
      STATUS      current
      DESCRIPTION
              "portPPPIndex"
      ::= { portPPPEntry 1}

  portPPPStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portPPPEntry 2}

  portPPPLocalIpAddr OBJECT-TYPE
      SYNTAX      IpAddress
      MAX-ACCESS  read-write
      STATUS      current
      DESCRIPTION
              "The IPv4 IP address of the Device Server end of the PPP
               link. For routing to work, you must enter a local IP
               address. Choose an address that is part of the same network
               or subnetwork as the remote end; for example, if the remote
               end is address 192.101.34.146, your local IP address can be
               192.101.34.145. Do not use the Device Server's (main) IP
               address in this field; if you do so, routing will not take
               place correctly."
      ::= { portPPPEntry 3}

  portPPPRemoteIpAddr OBJECT-TYPE
      SYNTAX      IpAddress
      MAX-ACCESS  read-write
      STATUS      current
      DESCRIPTION
              "The IPv4 IP address of the remote end of the PPP link. Choose an
               address that is part of the same network or subnetwork as the
               Device Server. If you set the PPP parameter IP Address Negotiation
               to On, the Device Server will ignore the remote IP address value
               you enter here and will allow the remote end to specify its IP
               address. If your user is authenticated by RADIUS and the RADIUS
               parameter Framed-Address is set in the RADIUS file, the Device
               Server will use the value in the RADIUS file in preference to the
               value configured here. The exception to this rule is a Framed-Address
               value in the RADIUS file of 255.255.255.254; this value allows the
               Device Server to use the remote IP address value configured here."
      ::= { portPPPEntry 4}

  portPPPSubnetBits OBJECT-TYPE
      SYNTAX      Integer32(0..32)
      MAX-ACCESS  read-write
      STATUS      current
      DESCRIPTION
              "The number of bits in the subnet mask. For example, a subnet mask
               of 255.255.0.0 has 16 subnet/prefix bits. If your user is
               authenticated by RADIUS and the RADIUS parameter Framed-Netmask is
               set in the RADIUS file, the Device Server will use the value in the
               RADIUS file in preference to the value configured here."
      ::= { portPPPEntry 5}

  portPPPIpV6LocalIpAddr OBJECT-TYPE
      SYNTAX      Ipv6InterfaceId
      MAX-ACCESS  read-write
      STATUS      current
      DESCRIPTION
              "The local IPv6 interface identifier of the Device Server end of the
               PPP link. For routing to work, you must enter a local IP address.
               Choose an address that is part of the same network or subnetwork as
               the remote end. Do not use the Device Server's (main) IP address in
               this field; if you do so, routing will not take place correctly. The
               first 64 bits of the Interface Identifier must be zero, therefore,
               ::abcd:abcd:abcd:abcd is the expected format."
      ::= { portPPPEntry 6}

  portPPPIpV6RemoteIpAddr OBJECT-TYPE
      SYNTAX      Ipv6InterfaceId
      MAX-ACCESS  read-write
      STATUS      current
      DESCRIPTION
              "The remote IPv6 interface identifier of the remote end of the PPP link.
               Choose an address that is part of the same network or subnetwork as the
               Device Server. If you set the PPP parameter IP Address Negotiation to On,
               the Device Server will ignore the remote IP address value you enter here
               and will allow the remote end to specify its IP address. If your user is
               authenticated by RADIUS and the RADIUS parameter Framed-Interface-ID is
               set in the RADIUS file, the Device Server will use the value in the RADIUS
               file in preference to the value configured here. The first 64 bits of the
               Interface Identifier must be zero, therefore, ::abcd:abcd:abcd:abcd is the
               expected format."
      ::= { portPPPEntry 7}

  portPPPAccm OBJECT-TYPE
      SYNTAX      Hex32
      MAX-ACCESS  read-write
      STATUS      current
      DESCRIPTION
              "Specifies the ACCM (Asynchronous Control Character Map) characters that
               should be escaped from the data stream. This is entered as a 32-bit
               hexadecimal number with each bit specifying whether or not the corresponding
               character should be escaped. The bits are specified as the most significant
               bit first and are numbered 31-0. Thus if bit 17 is set, the 17th character
               should be escaped, that is, 0x11 (XON). So entering the value 000a0000 will
               cause the control characters 0x11 (XON) and 0x13 (XOFF) to be escaped on the
               link, thus allowing the use of XON/XOFF (software) flow control. If you have
               selected Soft Flow Control on the Line, you must enter a value of 000a0000
               for the ACCM. The default value is 00000000, which means no characters will
               be escaped."
      ::= { portPPPEntry 8}

  portPPPMru OBJECT-TYPE
      SYNTAX      Integer32(64..1500)
      MAX-ACCESS  read-write
      STATUS      current
      DESCRIPTION
              "The Maximum Receive Unit (MRU) parameter specifies the maximum size of PPP
               packets that the Device Server's port will accept. Enter a value between
               64 and 1500 bytes; for example, 512. The default value is 1500. If your
               user is authenticated by the Device Server, the MRU value will be overridden
               if you have set a Framed MTU value for the user. If your user is authenticated
               by RADIUS and the RADIUS parameter Framed-MTU is set in the RADIUS file, the
               Device Server will use the value in the RADIUS file in preference to the
               value configured here."
      ::= { portPPPEntry 9}

  portPPPSecurity OBJECT-TYPE
      SYNTAX      INTEGER {
        none(1),
        pap(2),
        chap(3)
      }
      MAX-ACCESS  read-write
      STATUS      current
      DESCRIPTION
              "The type of authentication that will be done on the link: None, PAP, or CHAP.
               The default is CHAP. You can use PAP or CHAP to authenticate a port or user
               on the Device Server, from a remote location, or authenticate a remote
               client/device, from the Device Server. PAP is a one time challenge of a
               client/device requiring that it respond with a valid username and password.
               A timer operates during which successful authentication must take place. If
               the timer expires before the remote end has been authenticated successfully,
               the link will be terminated. CHAP challenges a client/device at regular
               intervals to validate itself with a username and a response, based on a hash
               of the secret (password). A timer operates during which successful
               authentication must take place. If the timer expires before the remote end
               has been authenticated successfully, the link will be terminated. When
               setting either PAP and CHAP, make sure the Device Server and the remote
               client/device have the same setting. For example, if the Device Server is set
               to PAP, but the remote end is set to CHAP, the connection will be refused. "
      ::= { portPPPEntry 10}

  portPPPUser OBJECT-TYPE
      SYNTAX      DisplayString(SIZE(0..254))
      MAX-ACCESS  read-write
      STATUS      current
      DESCRIPTION
              "Complete this field only if you have specified PAP or CHAP (security
               protocols) in the Security field, and you wish to dedicate this line
               to a single remote user, who will be authenticated by the Device Server,
               or you are using the Device Server as a router (back-to-back with
               another Device Server). When Dial is set to Out or Both, the User is the
               name the remote device will use to authenticate a port on this Device Server.
               The remote device will only authenticate your Device Server's port when PAP
               or CHAP are operating. You can enter a maximum of sixteen alphanumeric
               characters; for example, tracy201. When connecting together two networks,
               enter a dummy user name; for example, DS_HQ.
               Note If you want a reasonable level of security, the user name and password
               should not be similar to a user name or password used regularly to login to
               the Device Server. External authentication can not be used for this user."
      ::= { portPPPEntry 11}

  portPPPRemoteUser OBJECT-TYPE
      SYNTAX      DisplayString(SIZE(0..254))
      MAX-ACCESS  read-write
      STATUS      current
      DESCRIPTION
              "Complete this field only if you have specified PAP or CHAP (security protocols)
               in the Security field, and you wish to dedicate this line to a single remote
               user, who will be authenticated by the Device Server, or you are using the
               Device Server as a router (back-to-back with another Device Server) When Dial
               is set to In or Both, the Remote User is the name the Device Server will use
               to authenticate the port on the remote device. Your Device Server will only
               authenticate the port on the remote device when PAP or CHAP are operating.
               You can enter a maximum of sixteen alphanumeric characters. When connecting
               together two networks, enter a dummy user name; for example, DS_SALES.
               Note If you want a reasonable level of security, the user name and password
               should not be similar to a user name or password used regularly to login to
               the Device Server. This option does not work with external authentication."
      ::= { portPPPEntry 12}

  portPPPACComp OBJECT-TYPE
      SYNTAX      OnOffValue
      MAX-ACCESS  read-write
      STATUS      current
      DESCRIPTION
              "This determines whether compression of the PPP Address and Control fields
               take place on the link. The default is On. For most applications this should
               be enabled."
      ::= { portPPPEntry 13}

  portPPPProtoComp OBJECT-TYPE
      SYNTAX      OnOffValue
      MAX-ACCESS  read-write
      STATUS      current
      DESCRIPTION
              "This determines whether compression of the PPP Protocol field takes
               place on this link. The default is On."
      ::= { portPPPEntry 14}

  portPPPVJComp OBJECT-TYPE
      SYNTAX      OnOffValue
      MAX-ACCESS  read-write
      STATUS      current
      DESCRIPTION
              "This determines whether Van Jacobson Compression is used on this link.
               The default is On. If your user is authenticated by the Device Server,
               this VJ compression value will be overridden if you have set the User
               Framed Compression On. If your user is authenticated by RADIUS and the
               RADIUS parameter Framed-Compression is set in the RADIUS file, the
               Device Server will use the value in the RADIUS file in preference to
               the value configured here."
      ::= { portPPPEntry 15}

  portPPPMagicNegotiation OBJECT-TYPE
      SYNTAX      OnOffValue
      MAX-ACCESS  read-write
      STATUS      current
      DESCRIPTION
              "Determines if a line is looping back. If enabled (On), random
               numbers are sent on the link. The random numbers should be
               different, unless the link loops back. The default is Off. "
      ::= { portPPPEntry 16}

  portPPPIPAddrNegotiation OBJECT-TYPE
      SYNTAX      OnOffValue
      MAX-ACCESS  read-write
      STATUS      current
      DESCRIPTION
              "Specifies whether or not IP address negotiation will take place.
               IP address negotiation is where the Device Server allows the
               remote end to specify its IP address. The default value is Off.
               When On, the IP address specified by the remote end will be used
               in preference to the Remote IP Address set for a Line. When Off,
               the Remote IP Address set for the Line will be used. "
      ::= { portPPPEntry 17}

  portPPPCRTimeout OBJECT-TYPE
      SYNTAX      Integer32(1..255)
      MAX-ACCESS  read-write
      STATUS      current
      DESCRIPTION
              "The maximum time, in seconds, that LCP (Link Control Protocol)
               will wait before it considers a configure request packet to have
               been lost."
      ::= { portPPPEntry 18}

  portPPPTRTimeout OBJECT-TYPE
      SYNTAX      Integer32(1..255)
      MAX-ACCESS  read-write
      STATUS      current
      DESCRIPTION
              "The maximum time, in seconds, that LCP (Link Control Protocol)
               will wait before it considers a terminate request packet to have
               been lost."
      ::= { portPPPEntry 19}

  portPPPCRRetry OBJECT-TYPE
      SYNTAX      Integer32(0..255)
      MAX-ACCESS  read-write
      STATUS      current
      DESCRIPTION
              "The maximum number of times a configure request packet will
               be sent before the link is terminated."
      ::= { portPPPEntry 20}

  portPPPTRRetry OBJECT-TYPE
      SYNTAX      Integer32(0..255)
      MAX-ACCESS  read-write
      STATUS      current
      DESCRIPTION
              "The maximum number of times a terminate request packet will
               be sent before the link is terminated."
      ::= { portPPPEntry 21}

  portPPPNakRetry OBJECT-TYPE
      SYNTAX      Integer32(0..255)
      MAX-ACCESS  read-write
      STATUS      current
      DESCRIPTION
              "The maximum number of times a configure NAK packet will
               be sent before the link is terminated."
      ::= { portPPPEntry 22}

  portPPPAuthTimeout OBJECT-TYPE
      SYNTAX      Integer32(1..255)
      MAX-ACCESS  read-write
      STATUS      current
      DESCRIPTION
              "The timeout, in seconds, during which successful PAP or
               CHAP authentication must take place (when PAP or CHAP is
               turned On). If the timer expires before the remote end has
               been authenticated successfully, the link will be terminated."
      ::= { portPPPEntry 23}

  portPPPRoamingCallback OBJECT-TYPE
      SYNTAX      OnOffValue
      MAX-ACCESS  read-write
      STATUS      current
      DESCRIPTION
              "A user can enter a telephone number that the Device Server
               will use to callback him/her. This feature is particularly
               useful for a mobile user. Roaming callback can only work when
               the User Callback parameter is set to On. Roaming callback
               therefore overrides (fixed) User Callback.To use Roaming
               Callback, the remote end must be a Microsoft Windows OS that
               supports Microsoft's Callback Control Protocol (CBCP). The user
               is allowed 30 seconds to enter a telephone number after which
               the Device Server ends the call. The default is Off."
      ::= { portPPPEntry 24}

  portPPPChallengInterval OBJECT-TYPE
      SYNTAX      Integer32(0..255)
      MAX-ACCESS  read-write
      STATUS      current
      DESCRIPTION
              "The interval, in seconds, for which the Device Server will
               issue a CHAP re-challenge to the remote end. During CHAP
               authentication, an initial CHAP challenge takes place, and
               is unrelated to CHAP re-challenges. The initial challenge takes
               place even if re-challenges are disabled. Some PPP client software
               does not work with CHAP re-challenges, so you might want to leave
               the parameter disabled in the Device Server. The default value
               is 0 (zero), meaning CHAP re-challenge is disabled. "
      ::= { portPPPEntry 25}

   portPPPRouting OBJECT-TYPE
      SYNTAX      INTEGER {
        none(1),
        send(2),
        listen(3),
        sendAndListen(4)
      }
      MAX-ACCESS  read-write
      STATUS      current
      DESCRIPTION
              "Determines the routing mode (RIP, Routing Information Protocol)
               used on the PPP interface as one of the following options:
               None-Disables RIP over the PPP/SLIP interface.
               Send-Sends RIP over the PPP/SLIP interface.
               Listen-Listens for RIP over the PPP/SLIP interface.
               Send and Listen-Sends RIP and listens for RIP over the PPP/SLIP interface.
               This is the same function as the Framed-Routing attribute for
               RADIUS authenticated users. Default is None."
      ::= { portPPPEntry 26}

  portPPPDynamicDNSEnabled OBJECT-TYPE
      SYNTAX      OnOffValue
      MAX-ACCESS  read-write
      STATUS      current
      DESCRIPTION
              "Enable/disable dynamic DNS."
      ::= { portPPPEntry 27}

  portPPPDynamicDNSHostname OBJECT-TYPE
      SYNTAX      DisplayString(SIZE(1..14))
      MAX-ACCESS  read-write
      STATUS      current
      DESCRIPTION
              "Host name."
      ::= { portPPPEntry 28}
      
  portPPPDynamicDNSUserName OBJECT-TYPE
      SYNTAX      DisplayString(SIZE(1..16))
      MAX-ACCESS  read-write
      STATUS      current
      DESCRIPTION
              "user name."
      ::= { portPPPEntry 29}
      
  portPPPDynamicDNSPassword OBJECT-TYPE
      SYNTAX      DisplayString(SIZE(1..16))
      MAX-ACCESS  read-write
      STATUS      current
      DESCRIPTION
              "Password."
      ::= { portPPPEntry 30}
      
   portPPPDynamicDNSStatusString OBJECT-TYPE
      SYNTAX      OCTET STRING (SIZE(0..1024))
      MAX-ACCESS  read-write
      STATUS      current
      DESCRIPTION
              "Dynamic DNS Status"
      ::= { portPPPEntry 31}
      
    portPPPMSDirectConnection OBJECT-TYPE
      SYNTAX      INTEGER {
       disable(1),
       server(2),
       client(3)
      }
      MAX-ACCESS  read-write
      STATUS      current
      DESCRIPTION
              "Set for Microsoft PPP connection working mode"
      ::= { portPPPEntry 32}
	  
  portPPPIPv6Prefix OBJECT-TYPE
      SYNTAX      Ipv4v6Address
      MAX-ACCESS  read-write
      STATUS      current
      DESCRIPTION
              "You can optionally specify an IPv6 global network prefix
               that the Device Server will advertise to the device at the 
               other end of the PPP link. Default: 0:0:0:0"
      ::= { portPPPEntry 33 }

  portPPPIPv6PrefixBits OBJECT-TYPE
      SYNTAX      Integer32(0..128)
      MAX-ACCESS  read-write
      STATUS      current
      DESCRIPTION
              "Specify the prefix bits for the IPv6 global network prefix.
               Default is 64."
      ::= { portPPPEntry 34 }
	  
  portPPPEchoTimeout OBJECT-TYPE
      SYNTAX      Integer32(1..255)
      MAX-ACCESS  read-write
      STATUS      current
      DESCRIPTION
              "The timeout, in seconds, to wait for an Echo reply."
      ::= { portPPPEntry 35}

  portPPPEchoRetry OBJECT-TYPE
      SYNTAX      Integer32(0..255)
      MAX-ACCESS  read-write
      STATUS      current
      DESCRIPTION
              "The maximum number of Echo reply timeouts before
               the link is terminated."
      ::= { portPPPEntry 36}

-- Port Slip Table

  portSLIPTable OBJECT-TYPE
      SYNTAX      SEQUENCE OF PortSLIPEntry
      MAX-ACCESS  not-accessible
      STATUS      current
      DESCRIPTION
              "Port SLIP Table."
      ::= { portInfo 6 }

  portSLIPEntry OBJECT-TYPE
      SYNTAX      PortSLIPEntry
      MAX-ACCESS  not-accessible
      STATUS      current
      DESCRIPTION
              "An entry in the portSLIPEntry, each relating to a port."
      INDEX   { portSLIPIndex }
      ::= { portSLIPTable 1 }

  PortSLIPEntry ::=
      SEQUENCE {
        portSLIPIndex            PortNumber,
        portSlipStatus            ContainerStatus,
        portSLIPLocalIpAddress            IpAddress,
        portSLIPRemoteIpAddress            IpAddress,
        portSLIPSubnetBits            Integer32,
        portSLIPMtu            Integer32,
        portSLIPVJComp            OnOffValue,
        portSLIPRouting            INTEGER
      }

  portSLIPIndex OBJECT-TYPE
      SYNTAX      PortNumber
      MAX-ACCESS  not-accessible
      STATUS      current
      DESCRIPTION
              "portSLIPIndex"
      ::= { portSLIPEntry 1}

  portSlipStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portSLIPEntry 2}

  portSLIPLocalIpAddress OBJECT-TYPE
      SYNTAX      IpAddress
      MAX-ACCESS  read-write
      STATUS      current
      DESCRIPTION
              "The IPv4 address of the Device Server end of the SLIP
               link. For routing to work you must enter an IP address
               in this field. Choose an address that is part of the same
               network or subnetwork as the remote end; for example, if
               the remote end is address 192.101.34.146, your local IP
               address can be 192.101.34.145. Do not use the Device Server's
               (main) IP address in this field; if you do so, routing will not
               take place correctly."
      ::= { portSLIPEntry 3}

  portSLIPRemoteIpAddress OBJECT-TYPE
      SYNTAX      IpAddress
      MAX-ACCESS  read-write
      STATUS      current
      DESCRIPTION
              "The IPv4 address of the remote end of the SLIP link. Choose
               an address that is part of the same network or subnetwork as
               the Device Server. If your user is authenticated by the Device
               Server, this remote IP address will be overridden if you have
               set a Framed IP Address for the user. If your user is authenticated
               by RADIUS and the RADIUS parameter Framed-Address is set in the
               RADIUS file, the Device Server will use the value in the RADIUS
               file in preference to the value configured here."
      ::= { portSLIPEntry 4}

  portSLIPSubnetBits OBJECT-TYPE
      SYNTAX      Integer32(0..32)
      MAX-ACCESS  read-write
      STATUS      current
      DESCRIPTION
              "The number of bits in the subnet mask. For example,
               a subnet mask of 255.255.0.0 has 16 subnet/prefix bits.
               If your user is authenticated by RADIUS and the RADIUS
               parameter Framed-Netmask is set in the RADIUS file, the
               Device Server will use the value in the RADIUS file in
               preference to the value configured here."
      ::= { portSLIPEntry 5}

  portSLIPMtu OBJECT-TYPE
      SYNTAX      Integer32(256..1006)
      MAX-ACCESS  read-write
      STATUS      current
      DESCRIPTION
              "The Maximum Transmission Unit (MTU) parameter restricts
               the size of individual SLIP packets being sent by the
               Device Server. Enter a value between 256 and 1006 bytes;
               for example, 512. The default value is 256. If your user
               is authenticated by the Device Server, this MTU value will
               be overridden when you have set a Framed MTU value for the
               user. If your user is authenticated by RADIUS and the
               RADIUS parameter Framed-MTU is set in the RADIUS file, the
               Device Server will use the value in the RADIUS file in
               preference to the value configured here."
      ::= { portSLIPEntry 6}

  portSLIPVJComp OBJECT-TYPE
      SYNTAX      OnOffValue
      MAX-ACCESS  read-write
      STATUS      current
      DESCRIPTION
              "This determines whether Van Jacobson compression is used
               on this link; that is, whether you are using SLIP or
               C-SLIP (compressed SLIP). The choices are On (C-SLIP) or
               Off (SLIP). The default is On. C-SLIP greatly improves
               the performance of interactive traffic, such as Telnet
               or Rlogin. If your user is authenticated by the Device
               Server, this VJ compression value will be overridden if
               you have set a Framed Compression value for a user. If
               your user is authenticated by RADIUS and the RADIUS
               parameter Framed-Compression is set in the RADIUS file,
               the Device Server will use the value in the RADIUS file
               in preference to the value configured here."
      ::= { portSLIPEntry 7}

   portSLIPRouting OBJECT-TYPE
      SYNTAX      INTEGER {
        none(1),
        send(2),
        listen(3),
        sendAndListen(4)
      }
      MAX-ACCESS  read-write
      STATUS      current
      DESCRIPTION
              "Determines the routing mode (RIP, Routing Information Protocol)
               used on the SLIP interface as one of the following options:
               None-Disables RIP over the PPP/SLIP interface.
               Send-Sends RIP over the PPP/SLIP interface.
               Listen-Listens for RIP over the PPP/SLIP interface.
               Send and Listen-Sends RIP and listens for RIP over the PPP/SLIP interface.
               This is the same function as the Framed-Routing attribute for
               RADIUS authenticated users. Default is None."
      ::= { portSLIPEntry 8}

-- Port UDP Table

  portUDPTable OBJECT-TYPE
      SYNTAX      SEQUENCE OF PortUDPEntry
      MAX-ACCESS  not-accessible
      STATUS      current
      DESCRIPTION
              "Port UDP Table."
      ::= { portInfo 7 }

  portUDPEntry OBJECT-TYPE
      SYNTAX      PortUDPEntry
      MAX-ACCESS  not-accessible
      STATUS      current
      DESCRIPTION
              "An entry in the portUDPEntry, each relating to a port."
      INDEX   { portUDPIndex, portUDPEntryIndex }
      ::= { portUDPTable 1 }

  PortUDPEntry ::=
      SEQUENCE {
        portUDPIndex             PortNumber,
        portUDPEntryIndex        GenericTableIndex,
        portUDPStatus            ContainerStatus,
        portUDPStartAddress            Ipv4v6Address,
        portUDPEndAddress            Ipv4v6Address,
        portUDPPort            Integer32,
        portUDPDirection            INTEGER,
        portUDPOption            INTEGER,
        portUDPTunnelName     DisplayString
        }
        
  portUDPIndex OBJECT-TYPE
      SYNTAX      PortNumber
      MAX-ACCESS  not-accessible
      STATUS      current
      DESCRIPTION
              "portUDPIndex"
      ::= { portUDPEntry 1}

  portUDPEntryIndex OBJECT-TYPE
      SYNTAX      GenericTableIndex
      MAX-ACCESS  not-accessible
      STATUS      current
      DESCRIPTION
              "portUDPNumber"
      ::= { portUDPEntry 2}

  portUDPStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portUDPEntry 3}

  portUDPStartAddress OBJECT-TYPE
      SYNTAX      Ipv4v6Address
      MAX-ACCESS  read-write
      STATUS      current
      DESCRIPTION
              "The first host IP address in the range of IP addresses
               (for IPv4 or IPv6) that the Device Server will listen for
               messages from and/or send messages to"
      ::= { portUDPEntry 4}

  portUDPEndAddress OBJECT-TYPE
      SYNTAX      Ipv4v6Address
      MAX-ACCESS  read-write
      STATUS      current
      DESCRIPTION
              "The last host IP address in the range of IP addresses (for
               IPv4, not required for IPv6) that the Device Server will listen
               for messages from and/or send messages to."
      ::= { portUDPEntry 5}

  portUDPPort OBJECT-TYPE
      SYNTAX      Integer32(0..65535)
      MAX-ACCESS  read-write
      STATUS      current
      DESCRIPTION
              "The port that the Device Server will use to receive messages
               from or relay messages to servers/hosts."
      ::= { portUDPEntry 6}

  portUDPDirection OBJECT-TYPE
      SYNTAX      INTEGER {
        none(1),
        in(2),
        out(3),
        both(4)
      }
      MAX-ACCESS  read-write
      STATUS      current
      DESCRIPTION
              "The direction in which information is received or relayed:
               None-UDP service not enabled.
               In-LAN to serial.
               Out-Serial to LAN.
               Both-Messages are relayed both directions."
      ::= { portUDPEntry 7}

    portUDPOption OBJECT-TYPE
      SYNTAX      INTEGER {
        specificOrAutoLearn(1),
        anyPort(2)
      }
      MAX-ACCESS  read-write
      STATUS      current
      DESCRIPTION
              "when want UDP port be any port which only valid for lan to serial direction set this to 2, 
               others for auto lean UDP port and specific port set this to 1"
      ::= { portUDPEntry 8}

  portUDPTunnelName OBJECT-TYPE
      SYNTAX      DisplayString(SIZE(0..14))
      MAX-ACCESS  read-write
      STATUS      current
      DESCRIPTION
              "The name of the HTTP tunnel associated with this service."
      ::= { portUDPEntry 9 }
  
-- Port Vmodem Table

  portVmodemTable OBJECT-TYPE
      SYNTAX      SEQUENCE OF PortVmodemEntry
      MAX-ACCESS  not-accessible
      STATUS      current
      DESCRIPTION
              "Port Vmodem Table."
      ::= { portInfo 8 }

  portVmodemEntry OBJECT-TYPE
      SYNTAX      PortVmodemEntry
      MAX-ACCESS  not-accessible
      STATUS      current
      DESCRIPTION
              "An entry in the portVmodemEntry, each relating to a port."
      INDEX   { portVmodemIndex }
      ::= { portVmodemTable 1 }

  PortVmodemEntry ::=
      SEQUENCE {
        portVmodemIndex            PortNumber,
        portVmodemStatus            ContainerStatus,
        portVmodemHost            DisplayString,
        portVmodemPort            Integer32,
        portVmodemSuccessString            DisplayString,
        portVmodemFailureString            DisplayString,
        portVmodemSuppress            OnOffValue,
        portVmodemStyle            INTEGER,
        portVmodemResponseDelay            Integer32,
        portVmodemEcho            OnOffValue,
        portVmodemMode            INTEGER,
        portVmodemDCD            INTEGER,
        portVmodemRTS            INTEGER,
        portVmodemDTR            INTEGER,
        portVmodemInitString     DisplayString,
        portVmodemTunnelName     DisplayString
        }
  portVmodemIndex OBJECT-TYPE
      SYNTAX      PortNumber
      MAX-ACCESS  not-accessible
      STATUS      current
      DESCRIPTION
              "portVmodemIndex"
      ::= { portVmodemEntry 1}

  portVmodemStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portVmodemEntry 2}

  portVmodemHost OBJECT-TYPE
      SYNTAX      DisplayString(SIZE(0..14))
      MAX-ACCESS  read-write
      STATUS      current
      DESCRIPTION
              "The target host name."
      ::= { portVmodemEntry 3}

  portVmodemPort OBJECT-TYPE
      SYNTAX      Integer32(0..65535)
      MAX-ACCESS  read-write
      STATUS      current
      DESCRIPTION
              "The port number the target host is listening on for messages."
      ::= { portVmodemEntry 4}

  portVmodemSuccessString OBJECT-TYPE
      SYNTAX      DisplayString(SIZE(0..40))
      MAX-ACCESS  read-write
      STATUS      current
      DESCRIPTION
              "String that is sent to the serial device when a connection
               succeeds. If no string is entered, then the string CONNECT
               will be sent with the connecting speed, for example CONNECT 9600."
      ::= { portVmodemEntry 5}

  portVmodemFailureString OBJECT-TYPE
      SYNTAX      DisplayString(SIZE(0..30))
      MAX-ACCESS  read-write
      STATUS      current
      DESCRIPTION
              "String that is sent to the serial device when a connection fails.
               If no string is entered, then the string NO CARRIER will be sent."
      ::= { portVmodemEntry 6}

  portVmodemSuppress OBJECT-TYPE
      SYNTAX      OnOffValue
      MAX-ACCESS  read-write
      STATUS      current
      DESCRIPTION
              "If set to No, connection success/failure indication strings are
               sent to the connected device, otherwise these indications
               are suppressed."
      ::= { portVmodemEntry 7}

  portVmodemStyle OBJECT-TYPE
      SYNTAX      INTEGER {
        numeric(1),
        verbose(2)
      }
      MAX-ACCESS  read-write
      STATUS      current
      DESCRIPTION
              "One of the following:
               Verbose-Return codes (strings) are sent to the connected device.
               Numeric-The following characters can be sent to the connected device:
                 1  Successfully Connected
                 2  Failed to Connect
                 4  Error"
      ::= { portVmodemEntry 8}

  portVmodemResponseDelay OBJECT-TYPE
      SYNTAX      Integer32(0..999)
      MAX-ACCESS  read-write
      STATUS      current
      DESCRIPTION
              "The vmodem delay to response, in milliseconds, default is 250."
      ::= { portVmodemEntry 9}

  portVmodemEcho OBJECT-TYPE
      SYNTAX      OnOffValue
      MAX-ACCESS  read-write
      STATUS      current
      DESCRIPTION
              "If set to on, vmodem will echo input."
      ::= { portVmodemEntry 10}
  portVmodemMode OBJECT-TYPE
      SYNTAX      INTEGER {
        auto(1),
        manual(2)
      }
      MAX-ACCESS  read-write
      STATUS      current
      DESCRIPTION
              "In auto mode vmodem will automatically use the host and port make connection,
              otherwise will wait for use input"
      ::= { portVmodemEntry 11}     

  portVmodemDCD OBJECT-TYPE
      SYNTAX      INTEGER {
        alwaysHigh(1),
        followConnection(2)
      }
      MAX-ACCESS  read-write
      STATUS      current
      DESCRIPTION
              "Define the behavior of DCD"
      ::= { portVmodemEntry 12}     

  portVmodemRTS OBJECT-TYPE
      SYNTAX      INTEGER {
        alwaysHigh(1),
        representDCD(4),
        representRI(5)
      }
      MAX-ACCESS  read-write
      STATUS      current
      DESCRIPTION
              "Define the behavior of signal RTS"
      ::= { portVmodemEntry 13}    

  portVmodemDTR OBJECT-TYPE
      SYNTAX      INTEGER {
        alwaysHigh(1),
        representDCD(3),
        representRI(4)
      }
      MAX-ACCESS  read-write
      STATUS      current
      DESCRIPTION
              "Define the behavior of signal DTR"
      ::= { portVmodemEntry 14}   

   portVmodemInitString OBJECT-TYPE
      SYNTAX      DisplayString(SIZE(0..255))
      MAX-ACCESS  read-write
      STATUS      current
      DESCRIPTION
              "String that used as initial AT commands."
      ::= { portVmodemEntry 15}

  portVmodemTunnelName OBJECT-TYPE
      SYNTAX      DisplayString(SIZE(0..14))
      MAX-ACCESS  read-write
      STATUS      current
      DESCRIPTION
              "The name of the HTTP tunnel associated with this service."
      ::= { portVmodemEntry 16 }
      
 -- Port Raw Table

  portRawTable OBJECT-TYPE
      SYNTAX      SEQUENCE OF PortRawEntry
      MAX-ACCESS  not-accessible
      STATUS      current
      DESCRIPTION
              "Port Raw Table."
      ::= { portInfo 9 }

  portRawEntry OBJECT-TYPE
      SYNTAX      PortRawEntry
      MAX-ACCESS  not-accessible
      STATUS      current
      DESCRIPTION
              "An entry in the portRawEntry, each relating to a port."
      INDEX   { portRawIndex }
      ::= { portRawTable 1 }

  PortRawEntry ::=
      SEQUENCE {
        portRawIndex            PortNumber,
        portRawStatus            ContainerStatus,
        portRawPort            Integer32,
        portRawHost            DisplayString,
        portRawTunnelName      DisplayString
        }
  portRawIndex OBJECT-TYPE
      SYNTAX      PortNumber
      MAX-ACCESS  not-accessible
      STATUS      current
      DESCRIPTION
              "Index of the corresponding serial port."
      ::= { portRawEntry 1}

  portRawStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portRawEntry 2}

  portRawPort OBJECT-TYPE
      SYNTAX      Integer32(0..65535)
      MAX-ACCESS  read-write
      STATUS      current
      DESCRIPTION
              "The port number the target host is listening on for incoming connections."
      ::= { portRawEntry 3}

  portRawHost OBJECT-TYPE
      SYNTAX      DisplayString (SIZE(0..14))
      MAX-ACCESS  read-write
      STATUS      current
      DESCRIPTION
              "The name of the target host."
      ::= { portRawEntry 4}
  
  portRawTunnelName OBJECT-TYPE
      SYNTAX      DisplayString(SIZE(0..14))
      MAX-ACCESS  read-write
      STATUS      current
      DESCRIPTION
              "The name of the HTTP tunnel associated with this service."
      ::= { portRawEntry 5 }

-- Port Bidir Table

  portBidirTable OBJECT-TYPE
      SYNTAX      SEQUENCE OF PortBidirEntry
      MAX-ACCESS  not-accessible
      STATUS      current
      DESCRIPTION
              "Port Bidir Table."
      ::= { portInfo 10 }

  portBidirEntry OBJECT-TYPE
      SYNTAX      PortBidirEntry
      MAX-ACCESS  not-accessible
      STATUS      current
      DESCRIPTION
              "An entry in the portBidirEntry, each relating to a port."
      INDEX   { portBidirIndex }
      ::= { portBidirTable 1 }

  PortBidirEntry ::=
      SEQUENCE {
        portBidirIndex            PortNumber,
        portBidirStatus            ContainerStatus,
        portBidirPort            Integer32,
        portBidirHost            DisplayString,
        portBidirTunnelName      DisplayString
        }
  portBidirIndex OBJECT-TYPE
      SYNTAX      PortNumber
      MAX-ACCESS  not-accessible
      STATUS      current
      DESCRIPTION
              "portBidirIndex"
      ::= { portBidirEntry 1}

  portBidirStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portBidirEntry 2}

  portBidirPort OBJECT-TYPE
      SYNTAX      Integer32(0..65535)
      MAX-ACCESS  read-write
      STATUS      current
      DESCRIPTION
              "The port number the target host is listening on for incoming connections."
      ::= { portBidirEntry 3}

  portBidirHost OBJECT-TYPE
      SYNTAX      DisplayString(SIZE(0..14))
      MAX-ACCESS  read-write
      STATUS      current
      DESCRIPTION
              "The name of the target host."
      ::= { portBidirEntry 4}

  portBidirTunnelName OBJECT-TYPE
      SYNTAX      DisplayString(SIZE(0..14))
      MAX-ACCESS  read-write
      STATUS      current
      DESCRIPTION
              "The name of the HTTP tunnel associated with this service's target host."
      ::= { portBidirEntry 5 }
  
-- Port Rlogin Table

  portRloginTable OBJECT-TYPE
      SYNTAX      SEQUENCE OF PortRloginEntry
      MAX-ACCESS  not-accessible
      STATUS      current
      DESCRIPTION
              "Port Rlogin Table."
      ::= { portInfo 11 }

  portRloginEntry OBJECT-TYPE
      SYNTAX      PortRloginEntry
      MAX-ACCESS  not-accessible
      STATUS      current
      DESCRIPTION
              "An entry in the portRloginEntry, each relating to a port."
      INDEX   { portRloginIndex }
      ::= { portRloginTable 1 }

  PortRloginEntry ::=
      SEQUENCE {
        portRloginIndex            PortNumber,
        portRloginStatus            ContainerStatus,
        portRloginHost            DisplayString,
        portRloginTermType            DisplayString,
        portRloginTunnelName      DisplayString
        }
 
  portRloginIndex OBJECT-TYPE
      SYNTAX      PortNumber
      MAX-ACCESS  not-accessible
      STATUS      current
      DESCRIPTION
              "Index of the corresponding serial port."
      ::= { portRloginEntry 1}

  portRloginStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portRloginEntry 2}

  portRloginHost OBJECT-TYPE
      SYNTAX      DisplayString(SIZE(0..14))
      MAX-ACCESS  read-write
      STATUS      current
      DESCRIPTION
              "The name of the target host."
      ::= { portRloginEntry 3}

  portRloginTermType OBJECT-TYPE
      SYNTAX      DisplayString(SIZE(0..14))
      MAX-ACCESS  read-write
      STATUS      current
      DESCRIPTION
              "Type of terminal attached to this line; for
               example, ANSI or WYSE60."
      ::= { portRloginEntry 4}

   
  portRloginTunnelName OBJECT-TYPE
      SYNTAX      DisplayString(SIZE(0..14))
      MAX-ACCESS  read-write
      STATUS      current
      DESCRIPTION
              "The name of the HTTP tunnel associated with this service."
      ::= { portRloginEntry 5 }

-- Port Email Table

  portEmailTable OBJECT-TYPE
      SYNTAX      SEQUENCE OF PortEmailEntry
      MAX-ACCESS  not-accessible
      STATUS      current
      DESCRIPTION
              "Port Email Table."
      ::= { portInfo 12 }

  portEmailEntry OBJECT-TYPE
      SYNTAX      PortEmailEntry
      MAX-ACCESS  not-accessible
      STATUS      current
      DESCRIPTION
              "An entry in the portEmailEntry, each relating to a port."
      INDEX   { portEmailIndex }
      ::= { portEmailTable 1 }

  PortEmailEntry ::=
      SEQUENCE {
        portEmailIndex              PortNumber,
         portEmailStatus            ContainerStatus,
         portEmailActive            OnOffValue,
         portEmailLevel             INTEGER,
         portEmailTo                DisplayString,
         portEmailFrom              DisplayString,
         portEmailReply             DisplayString,
         portEmailSubject           DisplayString,
         portEmailUseDefaultLevel   OnOffValue,
         portEmailUseDefaultTo      OnOffValue,
         portEmailUseDefaultFrom    OnOffValue,
         portEmailUseDefaultReply   OnOffValue,
         portEmailUseDefaultSubject OnOffValue
        }
  portEmailIndex OBJECT-TYPE
      SYNTAX      PortNumber
      MAX-ACCESS  not-accessible
      STATUS      current
      DESCRIPTION
              "Index of the corresponding serial port."
      ::= { portEmailEntry 1}

  portEmailStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portEmailEntry 2}

   portEmailActive OBJECT-TYPE
      SYNTAX      OnOffValue
      MAX-ACCESS  read-write
      STATUS      current
      DESCRIPTION
              "Determines whether or not email notification
               is turned on. Default is Off."
      ::= { portEmailEntry 3}

   portEmailLevel OBJECT-TYPE
      SYNTAX      INTEGER {
        emergency(1),
        alert(2),
        critical(3),
        error(4),
        warning(5),
        notice(6),
        informational(7),
        debug(8)
      }
      MAX-ACCESS  read-write
      STATUS      current
      DESCRIPTION
              "Choose the event level that triggers an email notification:
               Emergency, Alert, Critical, Error, Warning, Notice, Info, or
               Debug. You are selecting the lowest notification level;
               therefore, when you select Debug, you will get an email
               notification for all events that trigger a message."
      ::= { portEmailEntry 5}

   portEmailTo OBJECT-TYPE
      SYNTAX      DisplayString(SIZE(0..64))
      MAX-ACCESS  read-write
      STATUS      current
      DESCRIPTION
              "An email address or list of email addresses that will
               receive the email notification."
      ::= { portEmailEntry 6}

   portEmailFrom OBJECT-TYPE
      SYNTAX      DisplayString(SIZE(0..32))
      MAX-ACCESS  read-write
      STATUS      current
      DESCRIPTION
              "This field can contain an email address that might
               identify the Device Server name or some other value."
      ::= { portEmailEntry 7}

   portEmailReply OBJECT-TYPE
      SYNTAX      DisplayString(SIZE(0..32))
      MAX-ACCESS  read-write
      STATUS      current
      DESCRIPTION
              "The email address to whom all replies to the email
               notification should go."
      ::= { portEmailEntry 9}

   portEmailSubject OBJECT-TYPE
      SYNTAX      DisplayString(SIZE(0..48))
      MAX-ACCESS  read-write
      STATUS      current
      DESCRIPTION
              "A text string, which can contain spaces, that will
               display in the Subject field of the email notification."
      ::= { portEmailEntry 10}

   portEmailUseDefaultLevel OBJECT-TYPE
      SYNTAX      OnOffValue
      MAX-ACCESS  read-write
      STATUS      current
      DESCRIPTION
              "Inherit 'level' setting from the Server Email Alert."
      ::= { portEmailEntry 11}
      
   portEmailUseDefaultTo OBJECT-TYPE
      SYNTAX      OnOffValue
      MAX-ACCESS  read-write
      STATUS      current
      DESCRIPTION
              "Inherit 'to' setting from the Server Email Alert."
      ::= { portEmailEntry 12}
      
   portEmailUseDefaultFrom OBJECT-TYPE
      SYNTAX      OnOffValue
      MAX-ACCESS  read-write
      STATUS      current
      DESCRIPTION
              "Inherit 'from' setting from the Server Email Alert."
      ::= { portEmailEntry 13}

   portEmailUseDefaultReply OBJECT-TYPE
      SYNTAX      OnOffValue
      MAX-ACCESS  read-write
      STATUS      current
      DESCRIPTION
              "Inherit 'reply' setting from the Server Email Alert."
      ::= { portEmailEntry 14}
      
   portEmailUseDefaultSubject OBJECT-TYPE
      SYNTAX      OnOffValue
      MAX-ACCESS  read-write
      STATUS      current
      DESCRIPTION
              "Inherit 'subject' setting from the Server Email Alert."
      ::= { portEmailEntry 15}
      
      
-- Port SSL Info

  portSSLTable OBJECT-TYPE
      SYNTAX      SEQUENCE OF PortSSLEntry
      MAX-ACCESS  not-accessible
      STATUS      current
      DESCRIPTION
              "Port SSL Table."
      ::= { portInfo 13 }

  portSSLEntry OBJECT-TYPE
      SYNTAX      PortSSLEntry
      MAX-ACCESS  not-accessible
      STATUS      current
      DESCRIPTION
              "An entry in the portSSLEntry, each relating to a port."
      INDEX   { portSSLIndex }
      ::= { portSSLTable 1 }
  PortSSLEntry ::=
     SEQUENCE {
         portSSLIndex        PortNumber,
       portSSLStatus                ContainerStatus,
       portSSLEnabled               OnOffValue,
       portSSLuseServer             OnOffValue,
       portSSLVersion               INTEGER,
       portSSLType                  INTEGER,
       portSSLVerifyPeerCertificate OnOffValue,
       portSSLCountry               DisplayString,
       portSSLStateProv             DisplayString,
       portSSLLocality              DisplayString,
       portSSLOrganisation          DisplayString,
       portSSLOrganisationUnit      DisplayString,
       portSSLCommonName            DisplayString,
       portSSLEmail                 DisplayString
     }

  portSSLIndex OBJECT-TYPE
      SYNTAX      PortNumber
      MAX-ACCESS  not-accessible
      STATUS      current
      DESCRIPTION
              "port SSL Index"
      ::= { portSSLEntry 1}

  portSSLStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {portSSLEntry 2}

  portSSLEnabled  OBJECT-TYPE
      SYNTAX   OnOffValue
      MAX-ACCESS    read-write
      STATUS        current
      DESCRIPTION
                "Enables/disables SSL."
      ::= {portSSLEntry 3}

  portSSLuseServer  OBJECT-TYPE
      SYNTAX   OnOffValue
      MAX-ACCESS    read-write
      STATUS        current
      DESCRIPTION
                "Uses the SSL/TLS server configuration for the line."
      ::= {portSSLEntry 4}

  portSSLVersion  OBJECT-TYPE
      SYNTAX      INTEGER {
        any(1),
        tlsv1(2),
        sslv3(3)
      }
      MAX-ACCESS    read-write
      STATUS        current
      DESCRIPTION
                "Specify whether you want to use:
                 Any-The Device Server will try a TLSv1 connection first.
                     If that fails, it will try an SSLv3 connection. 
                     If that fails, it will try an SSLv2 connection.
                 TLSv1-The connection will use only TLSv1.
                 SSLv3-The connection will use only SSLv3.
                 The default is Any."
      ::= {portSSLEntry 5}

  portSSLType    OBJECT-TYPE
      SYNTAX      INTEGER {
        client(1),
        server(2)
      }
      MAX-ACCESS    read-write
      STATUS        current
      DESCRIPTION
                "Specify whether the Device Server will act as an 
                 SSL/TLS client or server. The default is Client."
      ::= {portSSLEntry 6}

  portSSLVerifyPeerCertificate  OBJECT-TYPE
      SYNTAX   OnOffValue
      MAX-ACCESS    read-write
      STATUS        current
      DESCRIPTION
                "Enable this option when you want the Validation Criteria
                 to match the Peer Certificate for authentication to pass.
                 If you enable this option, you need to download an  
                 SSL/TLS certificate authority (CA) list file to the 
                 Device Server. Any values that are entered in the validation
                 criteria must match the peer certificate for an SSL connection;
                 any fields left blank will not be validated against the peer 
                 certificate."
      ::= {portSSLEntry 7}

  portSSLCountry    OBJECT-TYPE
      SYNTAX      DisplayString(SIZE(0..2))
      MAX-ACCESS    read-write
      STATUS        current
      DESCRIPTION
                "A two character country code; for example, US."
      ::= {portSSLEntry 8}

  portSSLStateProv    OBJECT-TYPE
      SYNTAX      DisplayString(SIZE(0..128))
      MAX-ACCESS    read-write
      STATUS        current
      DESCRIPTION
                "Up to a 128 character entry for the state/province;
                 for example, IL."
      ::= {portSSLEntry 9}

  portSSLLocality    OBJECT-TYPE
      SYNTAX      DisplayString(SIZE(0..128))
      MAX-ACCESS    read-write
      STATUS        current
      DESCRIPTION
                "Up to a 128 character entry for the location; 
                 for example, a city."
      ::= {portSSLEntry 10}

  portSSLOrganisation    OBJECT-TYPE
      SYNTAX      DisplayString(SIZE(0..64))
      MAX-ACCESS    read-write
      STATUS        current
      DESCRIPTION
                "Up to a 64 character entry for the organization; 
                 for example, Accounting."
      ::= {portSSLEntry 11}

  portSSLOrganisationUnit    OBJECT-TYPE
      SYNTAX      DisplayString(SIZE(0..64))
      MAX-ACCESS    read-write
      STATUS        current
      DESCRIPTION
                "Up to a 64 character entry for the unit in the 
                 organization; for example, Payroll."
      ::= {portSSLEntry 12}

  portSSLCommonName    OBJECT-TYPE
      SYNTAX      DisplayString(SIZE(0..64))
      MAX-ACCESS    read-write
      STATUS        current
      DESCRIPTION
                "Up to a 64 character entry for common name; for example,
                 the host name or fully qualified domain name."
      ::= {portSSLEntry 13}

  portSSLEmail    OBJECT-TYPE
      SYNTAX      DisplayString(SIZE(0..128))
      MAX-ACCESS    read-write
      STATUS        current
      DESCRIPTION
                "Up to a 64 character entry for an email address; 
                 for example, acct@anycompany.com."
      ::= {portSSLEntry 14}

      
-- Packet Forwarding Table
  portPacketForwardingTable OBJECT-TYPE
      SYNTAX      SEQUENCE OF PortPacketForwardingEntry
      MAX-ACCESS  not-accessible
      STATUS      current
      DESCRIPTION
              "The port packet forwarding configuration table."
      ::= { portInfo 14 }

  portPacketForwardingEntry OBJECT-TYPE
      SYNTAX      PortPacketForwardingEntry
      MAX-ACCESS  not-accessible
      STATUS      current
      DESCRIPTION
              "An entry in the port packet forwarding configuration table, each relating to a serial port."
      INDEX   { portPacketForwardingIndex }
      ::= { portPacketForwardingTable 1 }

  PortPacketForwardingEntry ::=
      SEQUENCE {
          portPacketForwardingIndex              PortNumber,
          portPacketForwardingStatus               ContainerStatus,
          portPacketForwardingPacketSize              Integer32,
          portPacketForwardingIdleTime              Integer32,
          portPacketForwardingForceTransmitTime              Integer32,
          portPacketForwardingEnableSOF1              OnOffValue,
          portPacketForwardingSOF1              Hex8,
          portPacketForwardingEnableSOF2              OnOffValue,
          portPacketForwardingSOF2              Hex8,
          portPacketForwardingStartFrameTransmit              OnOffValue,
          portPacketForwardingEnableEOF1              OnOffValue,
          portPacketForwardingEOF1              Hex8,
          portPacketForwardingEnableEOF2              OnOffValue,
          portPacketForwardingEOF2              Hex8,
          portPacketForwardingEnableEndTrigger1              OnOffValue,
          portPacketForwardingEndTrigger1              Hex8,
          portPacketForwardingEnableEndTrigger2              OnOffValue,
          portPacketForwardingEndTrigger2              Hex8,
          portPacketForwardingForwardingRule              INTEGER,
          portPacketForwardingPacketIdleTime              Integer32,
          portPacketForwardingForwardMode              INTEGER
        }
  portPacketForwardingIndex OBJECT-TYPE
      SYNTAX      PortNumber
      MAX-ACCESS  not-accessible
      STATUS      current
      DESCRIPTION
              "Port Index"
      ::= { portPacketForwardingEntry 1}

  portPacketForwardingStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portPacketForwardingEntry 2}

  portPacketForwardingPacketSize OBJECT-TYPE
      SYNTAX      Integer32(0..1024)
      MAX-ACCESS  read-write
      STATUS      current
      DESCRIPTION
              "When the size of the packet equals this value the packet is 
               transmitted. 0 - Ignore option"
      ::= { portPacketForwardingEntry 3}

  portPacketForwardingIdleTime OBJECT-TYPE
      SYNTAX      Integer32(0..65535)
      MAX-ACCESS  read-write
      STATUS      current
      DESCRIPTION
              "When the elapsed time between one character to another character
               equals this value the packet is transmitted. 0 - Ignore option"
      ::= { portPacketForwardingEntry 4}

  portPacketForwardingForceTransmitTime OBJECT-TYPE
      SYNTAX      Integer32(0..65535)
      MAX-ACCESS  read-write
      STATUS      current
      DESCRIPTION
              "When the elapsed time from the 1st character received equals this
               value the packet is transmitted. 0 - Ignore option."
      ::= { portPacketForwardingEntry 5}

  portPacketForwardingEnableSOF1 OBJECT-TYPE
      SYNTAX     OnOffValue
      MAX-ACCESS  read-write
      STATUS      current
      DESCRIPTION
              "Enable/disable the start of frame 1."
      ::= { portPacketForwardingEntry 6}

  portPacketForwardingSOF1 OBJECT-TYPE
      SYNTAX      Hex8
      MAX-ACCESS  read-write
      STATUS      current
      DESCRIPTION
              "Any characters received before the start of frame is received will
               be ignored."
      ::= { portPacketForwardingEntry 7}

  portPacketForwardingEnableSOF2 OBJECT-TYPE
      SYNTAX     OnOffValue
      MAX-ACCESS  read-write
      STATUS      current
      DESCRIPTION
              "Enable/disable the start of frame 2. When this is enabled SOF1 must
               enabled"
      ::= { portPacketForwardingEntry 8}

  portPacketForwardingSOF2 OBJECT-TYPE
      SYNTAX      Hex8
      MAX-ACCESS  read-write
      STATUS      current
      DESCRIPTION
              "Any characters received before the start of frame is received will
               be ignored."
      ::= { portPacketForwardingEntry 9}
      
  portPacketForwardingStartFrameTransmit OBJECT-TYPE
      SYNTAX     OnOffValue
      MAX-ACCESS  read-write
      STATUS      current
      DESCRIPTION
              "A flag to determine if we will transmit the start of frame character(s)."
      ::= { portPacketForwardingEntry 10}
      
  portPacketForwardingEnableEOF1 OBJECT-TYPE
      SYNTAX     OnOffValue
      MAX-ACCESS  read-write
      STATUS      current
      DESCRIPTION
              "Enable/disable the end of frame 1."
      ::= { portPacketForwardingEntry 11}

  portPacketForwardingEOF1 OBJECT-TYPE
      SYNTAX      Hex8
      MAX-ACCESS  read-write
      STATUS      current
      DESCRIPTION
              "The frame will be transmitted after this character is received based on the
               forwarding rule."
      ::= { portPacketForwardingEntry 12}

  portPacketForwardingEnableEOF2 OBJECT-TYPE
      SYNTAX     OnOffValue
      MAX-ACCESS  read-write
      STATUS      current
      DESCRIPTION
              "Enable/disable the end of frame 2. When this is enabled EOF1 must
               enabled"
      ::= { portPacketForwardingEntry 13}

  portPacketForwardingEOF2 OBJECT-TYPE
      SYNTAX      Hex8
      MAX-ACCESS  read-write
      STATUS      current
      DESCRIPTION
              "The frame will be transmitted after this character is received based on the
               forwarding rule."
      ::= { portPacketForwardingEntry 14}
      
  portPacketForwardingEnableEndTrigger1 OBJECT-TYPE
      SYNTAX     OnOffValue
      MAX-ACCESS  read-write
      STATUS      current
      DESCRIPTION
              "Enable/disable the end of trigger 1."
      ::= { portPacketForwardingEntry 15}

  portPacketForwardingEndTrigger1 OBJECT-TYPE
      SYNTAX      Hex8
      MAX-ACCESS  read-write
      STATUS      current
      DESCRIPTION
              "When the end trigger is received the packet will transmitted based on the
               forwarding rules."
      ::= { portPacketForwardingEntry 16}

  portPacketForwardingEnableEndTrigger2 OBJECT-TYPE
      SYNTAX     OnOffValue
      MAX-ACCESS  read-write
      STATUS      current
      DESCRIPTION
              "Enable/disable the end of trigger 2. When this is enabled EOF1 must
               enabled"
      ::= { portPacketForwardingEntry 17}

  portPacketForwardingEndTrigger2 OBJECT-TYPE
      SYNTAX      Hex8
      MAX-ACCESS  read-write
      STATUS      current
      DESCRIPTION
              "When the end trigger is received the packet will transmitted based on the
               forwarding rules."
      ::= { portPacketForwardingEntry 18}
      
  portPacketForwardingForwardingRule OBJECT-TYPE
  SYNTAX      INTEGER {
      trigger (0),
      triggerplus1 (1),
      triggerplus2 (2),
      stripTrigger (3)
  }
      MAX-ACCESS  read-write
      STATUS      current
      DESCRIPTION
              "Forwarding rules."
      ::= { portPacketForwardingEntry 19}
      
   portPacketForwardingPacketIdleTime OBJECT-TYPE
      SYNTAX      Integer32(0..65535)
      MAX-ACCESS  read-write
      STATUS      current
      DESCRIPTION
              "When in Packet Accumulation mode it used for packet idle time"
      ::= { portPacketForwardingEntry 20}    
      
   portPacketForwardingForwardMode OBJECT-TYPE
	SYNTAX      INTEGER {
      forwardModeInvalid (0),
      optimizeEthernetTrafic (1),
      minimizeLatency (2),
      messageAccumulation (3),
      custom (4)
      }
      MAX-ACCESS  read-write
      STATUS      current
      DESCRIPTION
              "Forwarding Mode."
      ::= { portPacketForwardingEntry 21}
            
 -- Port Tunnel Table

  portTunnelTable OBJECT-TYPE
      SYNTAX      SEQUENCE OF PortTunnelEntry
      MAX-ACCESS  not-accessible
      STATUS      current
      DESCRIPTION
              "Port Tunnel Table."
      ::= { portInfo 15 }

  portTunnelEntry OBJECT-TYPE
      SYNTAX      PortTunnelEntry
      MAX-ACCESS  not-accessible
      STATUS      current
      DESCRIPTION
              "An entry in the portTunnelEntry, each relating to a port."
      INDEX   { portTunnelIndex }
      ::= { portTunnelTable 1 }

  PortTunnelEntry ::=
      SEQUENCE {
        portTunnelIndex       PortNumber,
        portTunnelStatus      ContainerStatus,
        portTunnelPort        Integer32,
        portTunnelHost        DisplayString,
        portTunnelHttpTunnelName    DisplayString
        }
  portTunnelIndex OBJECT-TYPE
      SYNTAX      PortNumber
      MAX-ACCESS  not-accessible
      STATUS      current
      DESCRIPTION
              "portTunnelIndex"
      ::= { portTunnelEntry 1}

  portTunnelStatus OBJECT-TYPE
      SYNTAX      ContainerStatus
      MAX-ACCESS  read-write
      STATUS      current
      DESCRIPTION
              "When you perform a GET on this variable, one of 
               the following values will be returned:
               1-Indicates that the container folder is active with no changes.
               2-Indicates that the container folder is active with change(s).
               Once you have completed setting the variables in a folder, you
               will want to submit your changes to the Device Server. To do 
               this, set the Status variable to 4. If you want to discard the
               changes, set the Status variable to 6.
               4-Indicates that the changes in the container folder are to be
                 submitted to the Device Server.
               6-Indicates that the changes in the container folder are to be
                 discarded."
      ::= { portTunnelEntry 2}

  portTunnelPort OBJECT-TYPE
      SYNTAX      Integer32(0..65535)
      MAX-ACCESS  read-write
      STATUS      current
      DESCRIPTION
              "The port number the target host is listening on for incoming connections."
      ::= { portTunnelEntry 3}

  portTunnelHost OBJECT-TYPE
      SYNTAX      DisplayString (SIZE(0..14))
      MAX-ACCESS  read-write
      STATUS      current
      DESCRIPTION
              "The name of the target host."
      ::= { portTunnelEntry 4}
  
  portTunnelHttpTunnelName OBJECT-TYPE
      SYNTAX      DisplayString(SIZE(0..14))
      MAX-ACCESS  read-write
      STATUS      current
      DESCRIPTION
              "The name of the HTTP tunnel associated with this service."
      ::= { portTunnelEntry 5 }
  
      
-- Port Modbus Slave Table

  portMODBUSSlaveTable OBJECT-TYPE
      SYNTAX      SEQUENCE OF PortMODBUSSlaveEntry
      MAX-ACCESS  not-accessible
      STATUS      current
      DESCRIPTION
              "Port Modbus Slave Table."
      ::= { portInfo 16 }

  portMODBUSSlaveEntry OBJECT-TYPE
      SYNTAX      PortMODBUSSlaveEntry
      MAX-ACCESS  not-accessible
      STATUS      current
      DESCRIPTION
              "An entry in the portMODBUSSlaveEntry, each relating to a port."
      INDEX   { portMODBUSSlaveIndex }
      ::= { portMODBUSSlaveTable 1 }

  PortMODBUSSlaveEntry ::=
      SEQUENCE {
        portMODBUSSlaveIndex            PortNumber,
        portMODBUSSlaveStatus            ContainerStatus,
        portMODBUSSlaveMode            INTEGER,
        portMODBUSSlaveCRLF            OnOffValue,
        portMODBUSSlaveUIDRange            DisplayString
      }
  portMODBUSSlaveIndex OBJECT-TYPE
      SYNTAX      PortNumber
      MAX-ACCESS  not-accessible
      STATUS      current
      DESCRIPTION
              "portMODBUSSlaveIndex"
      ::= { portMODBUSSlaveEntry 1}

  portMODBUSSlaveStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMODBUSSlaveEntry 2}

  portMODBUSSlaveMode OBJECT-TYPE
  SYNTAX      INTEGER {
	  rtu(0),
	  ascii(1)
  }
      MAX-ACCESS  read-write
      STATUS      current
      DESCRIPTION
              "Modbus serial device's mode: 0: RTU; 1: ASCII."
      ::= { portMODBUSSlaveEntry 3}

  portMODBUSSlaveCRLF OBJECT-TYPE
      SYNTAX      OnOffValue
      MAX-ACCESS  read-write
      STATUS      current
      DESCRIPTION
              "Enable/disable appending CR/LF"
      ::= { portMODBUSSlaveEntry 4}

  portMODBUSSlaveUIDRange OBJECT-TYPE
      SYNTAX      DisplayString(SIZE(0..40))
      MAX-ACCESS  read-write
      STATUS      current
      DESCRIPTION
              "The UID range for this entry."
      ::= { portMODBUSSlaveEntry 5 }
	        
-- Port Modbus Master Table

  portMODBUSMasterTable OBJECT-TYPE
      SYNTAX      SEQUENCE OF PortMODBUSMasterEntry
      MAX-ACCESS  not-accessible
      STATUS      current
      DESCRIPTION
              "Port Modbus Master Table."
      ::= { portInfo 17 }

  portMODBUSMasterEntry OBJECT-TYPE
      SYNTAX      PortMODBUSMasterEntry
      MAX-ACCESS  not-accessible
      STATUS      current
      DESCRIPTION
              "An entry in the portMODBUSMasterEntry, each relating to a port."
      INDEX   { portMODBUSMasterIndex }
      ::= { portMODBUSMasterTable 1 }

  PortMODBUSMasterEntry ::=
      SEQUENCE {
        portMODBUSMasterIndex            PortNumber,
        portMODBUSMasterStatus            ContainerStatus,
        portMODBUSMasterMode            INTEGER,
        portMODBUSMasterCRLF            OnOffValue
      }
  portMODBUSMasterIndex OBJECT-TYPE
      SYNTAX      PortNumber
      MAX-ACCESS  not-accessible
      STATUS      current
      DESCRIPTION
              "portMODBUSMasterIndex"
      ::= { portMODBUSMasterEntry 1}

  portMODBUSMasterStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMODBUSMasterEntry 2}

  portMODBUSMasterMode OBJECT-TYPE
  SYNTAX      INTEGER {
      rtu(0),
      ascii(1)
  }
      MAX-ACCESS  read-write
      STATUS      current
      DESCRIPTION
              "Modbus serial device's mode: 0: RTU; 1: ASCII."
      ::= { portMODBUSMasterEntry 3}

  portMODBUSMasterCRLF OBJECT-TYPE
      SYNTAX      OnOffValue
      MAX-ACCESS  read-write
      STATUS      current
      DESCRIPTION
              "Enable/disable appending CR/LF"
      ::= { portMODBUSMasterEntry 4}

-- Port CustomApp Table

  portCustomAppTable OBJECT-TYPE
      SYNTAX      SEQUENCE OF PortCustomAppEntry
      MAX-ACCESS  not-accessible
      STATUS      current
      DESCRIPTION
              "Port CustomApp Table."
      ::= { portInfo 18 }

  portCustomAppEntry OBJECT-TYPE
      SYNTAX      PortCustomAppEntry
      MAX-ACCESS  not-accessible
      STATUS      current
      DESCRIPTION
              "An entry in the PortCustomAppEntry, each relating to a port."
      INDEX   { portCustomAppIndex }
      ::= { portCustomAppTable 1 }

  PortCustomAppEntry ::=
      SEQUENCE {
        portCustomAppIndex            PortNumber,
        portCustomAppStatus            ContainerStatus,
        portCustomAppCommand            DisplayString
        }

 portCustomAppIndex OBJECT-TYPE
      SYNTAX      PortNumber
      MAX-ACCESS  not-accessible
      STATUS      current
      DESCRIPTION
              "portCustomAppIndex"
      ::= { portCustomAppEntry 1}


  portCustomAppStatus OBJECT-TYPE
      SYNTAX      ContainerStatus
      MAX-ACCESS  read-write
      STATUS      current
      DESCRIPTION
              "When you perform a GET on this variable, one of 
               the following values will be returned:
               1-Indicates that the container folder is active with no changes.
               2-Indicates that the container folder is active with change(s).
               Once you have completed setting the variables in a folder, you
               will want to submit your changes to the Device Server. To do 
               this, set the Status variable to 4. If you want to discard the
               changes, set the Status variable to 6.
               4-Indicates that the changes in the container folder are to be
                 submitted to the Device Server.
               6-Indicates that the changes in the container folder are to be
                 discarded."
      ::= { portCustomAppEntry 2}

  portCustomAppCommand OBJECT-TYPE
      SYNTAX      DisplayString(SIZE(0..80))
      MAX-ACCESS  read-write
      STATUS      current
      DESCRIPTION
              "The command line of the custom application."
      ::= { portCustomAppEntry 3}

  portTrueportServiceTable OBJECT-TYPE
      SYNTAX      SEQUENCE OF PortTrueportServiceEntry
      MAX-ACCESS  not-accessible
      STATUS      current
      DESCRIPTION
              "Port TrueportService Table."
      ::= { portInfo 19 }

  portTrueportServiceEntry OBJECT-TYPE
      SYNTAX      PortTrueportServiceEntry
      MAX-ACCESS  not-accessible
      STATUS      current
      DESCRIPTION
              "An entry in the portTrueportServiceEntry, each relating to a port."
      INDEX   { portTrueportServiceIndex }
      ::= { portTrueportServiceTable 1 }

  PortTrueportServiceEntry ::=
      SEQUENCE {
        portTrueportServiceIndex           PortNumber,
        portTrueportServiceStatus          ContainerStatus,
        portTrueportServicePort            Integer32,
        portTrueportServiceHost            DisplayString,
        portTrueportServiceClientInitiated	OnOffValue,
       portTrueportServiceActiveSignal     OnOffValue,
        portTrueportServiceTunnelName      DisplayString
        }
  portTrueportServiceIndex OBJECT-TYPE
      SYNTAX      PortNumber
      MAX-ACCESS  not-accessible
      STATUS      current
      DESCRIPTION
              "The index of the corresponding serial port."
      ::= { portTrueportServiceEntry 1}

  portTrueportServiceStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portTrueportServiceEntry 2}

  portTrueportServicePort OBJECT-TYPE
      SYNTAX      Integer32(0..65535)
      MAX-ACCESS  read-write
      STATUS      current
      DESCRIPTION
              "The port number the target host is listening on for incoming connections."
      ::= { portTrueportServiceEntry 3}

  portTrueportServiceHost OBJECT-TYPE
      SYNTAX      DisplayString (SIZE(0..14))
      MAX-ACCESS  read-write
      STATUS      current
      DESCRIPTION
              "The name of the target host."
      ::= { portTrueportServiceEntry 4}

  portTrueportServiceClientInitiated OBJECT-TYPE
      SYNTAX      OnOffValue
      MAX-ACCESS  read-write
      STATUS      current
      DESCRIPTION
              "Specifies whether or not the network connection is initiated 
               by the client"
      ::= {  portTrueportServiceEntry 5}

  portTrueportServiceActiveSignal OBJECT-TYPE
      SYNTAX      OnOffValue
      MAX-ACCESS  read-write
      STATUS      current
      DESCRIPTION
              "When the line becomes active, this option has the following impact:
               o Lite Mode-When enabled, the EIA-232 signals remain high (active) 
                 before, during, and after the session. When disabled, the 
                 EIA-232 signals remain low (inactive).
               o Full Mode-During the session, the client will be control the 
                 state of these signal before and after the connection.
               Default is on."
      ::= {  portTrueportServiceEntry 6}
  
 portTrueportServiceTunnelName OBJECT-TYPE
      SYNTAX      DisplayString(SIZE(0..14))
      MAX-ACCESS  read-write
      STATUS      current
      DESCRIPTION
              "The name of the HTTP tunnel associated with this service."
      ::= { portTrueportServiceEntry 7 }
    

-- Port Power Management Table

  portPowerManagementTable OBJECT-TYPE
      SYNTAX      SEQUENCE OF PortPowerManagementEntry
      MAX-ACCESS  not-accessible
      STATUS      current
      DESCRIPTION
              "Port Power Management Table."
      ::= { portInfo 20 }

  portPowerManagementEntry OBJECT-TYPE
      SYNTAX      PortPowerManagementEntry
      MAX-ACCESS  not-accessible
      STATUS      current
      DESCRIPTION
              "An entry in the portPowerManagementEntry, each relating to a port."
      INDEX   { portPowerManagementIndex }
      ::= { portPowerManagementTable 1 }

  PortPowerManagementEntry ::=
     SEQUENCE {
  portPowerManagementIndex      PortNumber,
        portPowerManagementStatus   ContainerStatus,
        portPowerManagementName     DisplayString,
        portPowerManagementModel    INTEGER
     }
  portPowerManagementIndex OBJECT-TYPE
      SYNTAX      PortNumber
      MAX-ACCESS  not-accessible
      STATUS      current
      DESCRIPTION
              "portPowerManagementIndex"
      ::= { portPowerManagementEntry 1}

  portPowerManagementStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portPowerManagementEntry 2}

  portPowerManagementName OBJECT-TYPE
      SYNTAX      DisplayString(SIZE(0..15))
      MAX-ACCESS  read-write
      STATUS      current
      DESCRIPTION
              "Power bar's name."
      ::= { portPowerManagementEntry 3}

  portPowerManagementModel OBJECT-TYPE
  SYNTAX      INTEGER {
      rps820(1),
      rps830(2),
      rps1620(3),
      rps1630(4)
  }
      MAX-ACCESS  read-write
      STATUS      current
      DESCRIPTION
              "Power bar's model"
      ::= { portPowerManagementEntry 4}
      

-- Port Multihost Table

  portMultihostTable OBJECT-TYPE
      SYNTAX      SEQUENCE OF PortMultihostEntry
      MAX-ACCESS  not-accessible
      STATUS      current
      DESCRIPTION
              "Port Multihost Table."
      ::= { portInfo 21 }

  portMultihostEntry OBJECT-TYPE
      SYNTAX      PortMultihostEntry
      MAX-ACCESS  not-accessible
      STATUS      current
      DESCRIPTION
              "An entry in the portMultihostEntry, each relating to a port."
      INDEX   { portMultihostIndex }
      ::= { portMultihostTable 1 }

  PortMultihostEntry ::=
      SEQUENCE {
        portMultihostIndex            PortNumber,
        portMultihostStatus            ContainerStatus,
        portMultihostMode            INTEGER
        }
  portMultihostIndex OBJECT-TYPE
      SYNTAX      PortNumber
      MAX-ACCESS  not-accessible
      STATUS      current
      DESCRIPTION
              "portMultihostIndex"
      ::= { portMultihostEntry 1 }

  portMultihostStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMultihostEntry 2}

  portMultihostMode OBJECT-TYPE
        SYNTAX      INTEGER {
        all(1),
        backup(2)
      }
      MAX-ACCESS  read-write
      STATUS      current
      DESCRIPTION
              "Set multihost operation mode.all:for muliple host list mode. backup: for primary-backup mode"
      ::= { portMultihostEntry 4}


-- Port multihost outbound Table

  portMultihostOutboundTable OBJECT-TYPE
      SYNTAX      SEQUENCE OF PortMultihostOutboundEntry
      MAX-ACCESS  not-accessible
      STATUS      current
      DESCRIPTION
              "Multihost outbound table."
      ::= { portInfo 22 }
      
  portMultihostOutboundEntry OBJECT-TYPE
      SYNTAX      PortMultihostOutboundEntry
      MAX-ACCESS  not-accessible
      STATUS      current
      DESCRIPTION
              "An entry in the portMultihostOutboundTable."
      INDEX   {portMultihostPortIndex, portMultihostOutboundIndex }
      ::= { portMultihostOutboundTable 1 }

  PortMultihostOutboundEntry ::=
      SEQUENCE {
        portMultihostPortIndex        PortNumber,
        portMultihostOutboundIndex        GenericTableIndex,
        portMultihostOutboundStatus        ContainerStatus,
        portMultihostOutboundHostID        DisplayString,
        portMultihostOutboundTcpPort        Integer32,
        portMultihostOutboundTunnel        DisplayString
      }

   portMultihostPortIndex OBJECT-TYPE
      SYNTAX      PortNumber
      MAX-ACCESS  not-accessible
      STATUS      current
      DESCRIPTION
              "The port number"
      ::= { portMultihostOutboundEntry 1 }
      
  portMultihostOutboundIndex OBJECT-TYPE
      SYNTAX      GenericTableIndex
      MAX-ACCESS  not-accessible
      STATUS      current
      DESCRIPTION
              "The outbound entry number"
      ::= { portMultihostOutboundEntry 2 }

  portMultihostOutboundStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMultihostOutboundEntry 3 }

  portMultihostOutboundHostID OBJECT-TYPE
      SYNTAX      DisplayString (SIZE(0..14))
      MAX-ACCESS  read-write
      STATUS      current
      DESCRIPTION
              "The host name."
      ::= { portMultihostOutboundEntry 4 }

  portMultihostOutboundTcpPort OBJECT-TYPE
      SYNTAX      Integer32(0..65535)
      MAX-ACCESS  read-write
      STATUS      current
      DESCRIPTION
              "The host TCP port."
      ::= { portMultihostOutboundEntry 5 }

  portMultihostOutboundTunnel OBJECT-TYPE
      SYNTAX      DisplayString (SIZE(0..14))
      MAX-ACCESS  read-write
      STATUS      current
      DESCRIPTION
              "The HTTP tunnel associated with this host."
      ::= { portMultihostOutboundEntry 6 }


-- Port Power Management Plug Table

  portPowerManagementPlugTable OBJECT-TYPE
      SYNTAX      SEQUENCE OF PortPowerManagementPlugEntry
      MAX-ACCESS  not-accessible
      STATUS      current
      DESCRIPTION
              "Power Management Plug Table."
      ::= { portInfo 23 }
      
  portPowerManagementPlugEntry OBJECT-TYPE
      SYNTAX      PortPowerManagementPlugEntry
      MAX-ACCESS  not-accessible
      STATUS      current
      DESCRIPTION
              "An entry in the portPowerManagementPlugTable, each relating to a plug."
      INDEX   {portPowerManagementPortIndex, portPowerManagementPlugIndex }
      ::= { portPowerManagementPlugTable 1 }

  PortPowerManagementPlugEntry ::=
      SEQUENCE {
         portPowerManagementPortIndex           PortNumber,
         portPowerManagementPlugIndex           GenericTableIndex,
         portPowerManagementPlugStatus          ContainerStatus,
         portPowerManagementPlugName            DisplayString,
         portPowerManagementPlugPowerUpInterval INTEGER,
         portPowerManagementPlugDefaultState    OnOffValue,
         portPowerManagementDSLine              PortNumber,
         portPowerManagementMonitorHost         DisplayString,
         portPowerManagementMonitorInterval     Integer32,
         portPowerManagementMonitorTimeout      Integer32,
         portPowerManagementMonitorRetries      Integer32,
         portPowerManagementMonitorEnableDelay  OnOffValue,
         portPowerManagementMonitorDelay        Integer32,
         portPowerManagementMonitorEnableConsoleMsg  OnOffValue,
         portPowerManagementMonitorEnableEmail  OnOffValue
      }

  portPowerManagementPortIndex OBJECT-TYPE
      SYNTAX      PortNumber
      MAX-ACCESS  not-accessible
      STATUS      current
      DESCRIPTION
              "The port number"
      ::= { portPowerManagementPlugEntry 1 }

  portPowerManagementPlugIndex OBJECT-TYPE
      SYNTAX      GenericTableIndex
      MAX-ACCESS  not-accessible
      STATUS      current
      DESCRIPTION
              "The plug number"
      ::= { portPowerManagementPlugEntry 2 }

  portPowerManagementPlugStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portPowerManagementPlugEntry 3 }

  portPowerManagementPlugName OBJECT-TYPE
      SYNTAX      DisplayString(SIZE(0..19))
      MAX-ACCESS  read-write
      STATUS      current
      DESCRIPTION
              "The plug's name."
      ::= { portPowerManagementPlugEntry 4 }

  portPowerManagementPlugPowerUpInterval OBJECT-TYPE
      SYNTAX      INTEGER {
        puIntervalHalf(1),
        puInterval1(2),
        puInterval2(3),
        puInterval5(4),
        puInterval15(5),
        puInterval30(6),
        puInterval60(7),
        puInterval120(8),
        puInterval180(9),
        puInterval300(10)
      }
      MAX-ACCESS  read-write
      STATUS      current
      DESCRIPTION
              "The plug's power up delay."
      ::= { portPowerManagementPlugEntry 5 }

  portPowerManagementPlugDefaultState OBJECT-TYPE
      SYNTAX      OnOffValue
      MAX-ACCESS  read-write
      STATUS      current
      DESCRIPTION
              "the plug's default state."
      ::= { portPowerManagementPlugEntry 6 }

  portPowerManagementDSLine OBJECT-TYPE
      SYNTAX      PortNumber
      MAX-ACCESS  read-write
      STATUS      current
      DESCRIPTION
              "the DS line number which the device on this plug is connected to(0:none, >0:corresponding to the 
               line number."
      ::= { portPowerManagementPlugEntry 7 }
      
  portPowerManagementMonitorHost OBJECT-TYPE
      SYNTAX      DisplayString (SIZE(0..14))
      MAX-ACCESS  read-write
      STATUS      current
      DESCRIPTION
              "The name of a host to monitor.  If the host fails to respond to pings,
               this plug's power will be cycled.  Set to a blank string to disable
               this feature."
      ::= { portPowerManagementPlugEntry 8 }
    
  portPowerManagementMonitorInterval OBJECT-TYPE
      SYNTAX      Integer32(0..255)
      MAX-ACCESS  read-write
      STATUS      current
      DESCRIPTION
              "The time between pings, in minutes."
      ::= { portPowerManagementPlugEntry 9 }

  portPowerManagementMonitorTimeout OBJECT-TYPE
      SYNTAX      Integer32(0..255)
      MAX-ACCESS  read-write
      STATUS      current
      DESCRIPTION
              "The amount of time to wait after pings, in seconds."
      ::= { portPowerManagementPlugEntry 10 }
      
  portPowerManagementMonitorRetries OBJECT-TYPE
      SYNTAX      Integer32(0..255)
      MAX-ACCESS  read-write
      STATUS      current
      DESCRIPTION
              "The number of times to retry pings."
      ::= { portPowerManagementPlugEntry 11 }
      
  portPowerManagementMonitorEnableDelay OBJECT-TYPE
      SYNTAX      OnOffValue
      MAX-ACCESS  read-write
      STATUS      current
      DESCRIPTION
              "Wait before cycling power, in the event of a monitor timeout."
      ::= { portPowerManagementPlugEntry 12 }
      
  portPowerManagementMonitorDelay OBJECT-TYPE
      SYNTAX      Integer32(0..255)
      MAX-ACCESS  read-write
      STATUS      current
      DESCRIPTION
              "Amount of time to wait before cycling power, in the event of a monitor timeout."
      ::= { portPowerManagementPlugEntry 13 }
      
  portPowerManagementMonitorEnableConsoleMsg OBJECT-TYPE
      SYNTAX      OnOffValue
      MAX-ACCESS  read-write
      STATUS      current
      DESCRIPTION
              "Display a message on the serial port, in the event of a monitor timeout,
               when power cycle delay is enabled.."
      ::= { portPowerManagementPlugEntry 14 }

  portPowerManagementMonitorEnableEmail OBJECT-TYPE
      SYNTAX      OnOffValue
      MAX-ACCESS  read-write
      STATUS      current
      DESCRIPTION
              "Send an email alert, in the event of a monitor timeout,
               when power cycle delay is enabled.."
      ::= { portPowerManagementPlugEntry 15 }
      


-- Port Modbus Master Slave Mapping Table

  portMODBUSMasterMappingTable OBJECT-TYPE
      SYNTAX      SEQUENCE OF PortMODBUSMasterMappingEntry
      MAX-ACCESS  not-accessible
      STATUS      current
      DESCRIPTION
              "Modbus Master Slave Mapping."
      ::= { portInfo 24 }
      
  portMODBUSMasterMappingEntry OBJECT-TYPE
      SYNTAX      PortMODBUSMasterMappingEntry
      MAX-ACCESS  not-accessible
      STATUS      current
      DESCRIPTION
              "An entry in the portMODBUSMasterMappingTable, each relating to a slave mapping."
      INDEX   {portMODBUSMasterPortIndex, portMODBUSMasterMappingIndex }
      ::= { portMODBUSMasterMappingTable 1 }

  PortMODBUSMasterMappingEntry ::=
      SEQUENCE {
         portMODBUSMasterPortIndex                     PortNumber,
         portMODBUSMasterMappingIndex           GenericTableIndex,
         portMODBUSMasterMappingStatus          ContainerStatus,
         portMODBUSMasterMappingRemoteIP        Ipv4v6Address,
         portMODBUSMasterMappingTransportType   INTEGER,
         portMODBUSMasterMappingPortNumber      Integer32,
         portMODBUSMasterMappingUIDStart        Integer32,
         portMODBUSMasterMappingUIDEnd          Integer32,
         portMODBUSMasterMappingUIDRangeMode    INTEGER,
         portMODBUSMasterMappingTunnelName      DisplayString
      }

  portMODBUSMasterPortIndex OBJECT-TYPE
      SYNTAX      PortNumber
      MAX-ACCESS  not-accessible
      STATUS      current
      DESCRIPTION
              "The port number"
      ::= { portMODBUSMasterMappingEntry 1 }
      
  portMODBUSMasterMappingIndex OBJECT-TYPE
      SYNTAX      GenericTableIndex
      MAX-ACCESS  not-accessible
      STATUS      current
      DESCRIPTION
              "The mapping table index"
      ::= { portMODBUSMasterMappingEntry 2 }

  portMODBUSMasterMappingStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portMODBUSMasterMappingEntry 3 }

  portMODBUSMasterMappingRemoteIP OBJECT-TYPE
      SYNTAX      Ipv4v6Address
      MAX-ACCESS  read-write
      STATUS      current
      DESCRIPTION
              "The remote slave's IP address."
      ::= { portMODBUSMasterMappingEntry 4 }

  portMODBUSMasterMappingTransportType OBJECT-TYPE
      SYNTAX      INTEGER {
        tcp(0),
        udp(1)
      }
      MAX-ACCESS  read-write
      STATUS      current
      DESCRIPTION
              "The remote slave's transport protocol type (TCP/UDP)."
      ::= { portMODBUSMasterMappingEntry 5 }

  portMODBUSMasterMappingPortNumber OBJECT-TYPE
      SYNTAX      Integer32(0..65535)
      MAX-ACCESS  read-write
      STATUS      current
      DESCRIPTION
              "the transport protocol layer port number (TCP/UDP)."
      ::= { portMODBUSMasterMappingEntry 6 }

  portMODBUSMasterMappingUIDStart OBJECT-TYPE
      SYNTAX      Integer32(1..247)
      MAX-ACCESS  read-write
      STATUS      current
      DESCRIPTION
              "The start UID of the UID range for this entry."
      ::= { portMODBUSMasterMappingEntry 7 }

  portMODBUSMasterMappingUIDEnd OBJECT-TYPE
      SYNTAX      Integer32(1..247)
      MAX-ACCESS  read-write
      STATUS      current
      DESCRIPTION
              "The end UID of the UID range for this entry."
      ::= { portMODBUSMasterMappingEntry 8 }
	  
  portMODBUSMasterMappingUIDRangeMode OBJECT-TYPE
  SYNTAX      INTEGER {
      host(0),
      gateway(1)
  }
      MAX-ACCESS  read-write
      STATUS      current
      DESCRIPTION
              "The UID-IP mapping mode."
      ::= { portMODBUSMasterMappingEntry 9 }
  
  portMODBUSMasterMappingTunnelName OBJECT-TYPE
      SYNTAX      DisplayString(SIZE(0..14))
      MAX-ACCESS  read-write
      STATUS      current
      DESCRIPTION
              "The name of the HTTP tunnel associated with this service."
      ::= { portMODBUSMasterMappingEntry 10 }
            
-- Port SSL Server Cipher Table

  portSSLCipherTable OBJECT-TYPE
      SYNTAX      SEQUENCE OF PortSSLCipherEntry
      MAX-ACCESS  not-accessible
      STATUS      current
      DESCRIPTION
              "SSL CIpher."
      ::= { portInfo 25 }
  
  portSSLCipherEntry OBJECT-TYPE
      SYNTAX      PortSSLCipherEntry
      MAX-ACCESS  not-accessible
      STATUS      current
      DESCRIPTION
              "An entry in the sslCipherTable, each relating to a cipher entry."
      INDEX   { portSSLCipherIndex, portSSLCipherPriority }
      ::= { portSSLCipherTable 1 }

  PortSSLCipherEntry ::=
     SEQUENCE {
        portSSLCipherIndex        PortNumber,
        portSSLCipherPriority      Integer32,
        portSSLCipherStatus        ContainerStatus,
        portSSLCipherEncryption    INTEGER,
        portSSLCipherKeySizeMin    INTEGER,
        portSSLCipherKeySizeMax    INTEGER,
        portSSLCipherKeyExchange   INTEGER,
        portSSLCipherHMAC          INTEGER
      }

  portSSLCipherIndex OBJECT-TYPE
      SYNTAX      PortNumber
      MAX-ACCESS  not-accessible
      STATUS      current
      DESCRIPTION
              "The port number"
      ::= { portSSLCipherEntry 1 }

  portSSLCipherPriority OBJECT-TYPE
      SYNTAX      Integer32(1..5)
      MAX-ACCESS  not-accessible
      STATUS      current
      DESCRIPTION
              "The cipher priority. 1- highest 5 - lowest."
      ::= { portSSLCipherEntry 2 }

  portSSLCipherStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { portSSLCipherEntry 3 }

  portSSLCipherEncryption OBJECT-TYPE
      SYNTAX      INTEGER {
        none(1),
        any(2),
        aes(3),
        tripledes(4),
        des(5),
        arctwo(6),
        arcfour(7)
      }
      MAX-ACCESS  read-write
      STATUS      current
      DESCRIPTION
              "SSL Encryption. None is not allowed for priority 1.
               Any will use the first encryption format that can be 
               negotiated. The default is any."
      ::= { portSSLCipherEntry 4 }

  portSSLCipherKeySizeMin OBJECT-TYPE
      SYNTAX      INTEGER {
        min40(1),
        min56(2),
        min64(3),
        min128(4),
        min168(5),
        min256(6)
      }
      MAX-ACCESS  read-write
      STATUS      current
      DESCRIPTION
              "The minimum key size value that will be used for 
               the specified encryption type. The default is 40."
      ::= { portSSLCipherEntry 5 }

  portSSLCipherKeySizeMax OBJECT-TYPE
      SYNTAX      INTEGER {
        max40(1),
        max56(2),
        max64(3),
        max128(4),
        max168(5),
        max256(6)
      }
      MAX-ACCESS  read-write
      STATUS      current
      DESCRIPTION
              "The maximum key size value that will be used for the
               specified encryption type. The default is 256."
      ::= { portSSLCipherEntry 6 }

  portSSLCipherKeyExchange OBJECT-TYPE
      SYNTAX      INTEGER {
        any(1),
        rsa(2),
        edhrsa(3),
        edhdss(4),
        adh(5)
      }
      MAX-ACCESS  read-write
      STATUS      current
      DESCRIPTION
              "The type of key to exchange for the encryption format:
               Any-Any key exchange that is valid is used (this does 
                   not, however, include ADH keys).
               RSA-This is an RSA key exchange using an RSA key and 
                   certificate.
               EDHRSA-This is an EDH key exchange using an RSA key 
                   and certificate.
               EDHDSS-This is an EDH key exchange using a DSA key
                   and certificate.
               ADH-This is an anonymous key exchange which does not 
                   require a private key or certificate. Choose this 
                   key if you do not want to authenticate the peer device, 
                   but you want the data encrypted on the SSL/TLS connection.
               The default is Any."
      ::= { portSSLCipherEntry 7 }

  portSSLCipherHMAC OBJECT-TYPE
      SYNTAX      INTEGER {
        any(1),
        sha(2),
        md5(3)
      }
      MAX-ACCESS  read-write
      STATUS      current
      DESCRIPTION
              "Select the key-hashing for message authentication method 
               for your encryption type: Any, MD5, or SHA1.
               The default is Any."
      ::= { portSSLCipherEntry 8 }


-- Modem Table

  modemInfoTable OBJECT-TYPE
      SYNTAX      SEQUENCE OF ModemInfoEntry
      MAX-ACCESS  not-accessible
      STATUS      current
      DESCRIPTION
              "The modem info table."
      ::= { modemInfo 1 }

  modemInfoEntry OBJECT-TYPE
      SYNTAX      ModemInfoEntry
      MAX-ACCESS  not-accessible
      STATUS      current
      DESCRIPTION
              "An entry in the modemInfoTable, each relating to a host."
      INDEX   { modemIndex }
      ::= { modemInfoTable 1 }

  ModemInfoEntry ::=
      SEQUENCE {
        modemIndex            GenericTableIndex,
        modemStatus           ContainerStatus,
        modemName             DisplayString,
        modemInitialisation   DisplayString
      }

  modemIndex OBJECT-TYPE
      SYNTAX      GenericTableIndex
      MAX-ACCESS  not-accessible
      STATUS      current
      DESCRIPTION
              "The table entry number for this modem"
      ::= { modemInfoEntry 1 }

  modemStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { modemInfoEntry 2 }

  modemName OBJECT-TYPE
      SYNTAX      DisplayString(SIZE(0..20))
      MAX-ACCESS  read-write
      STATUS      current
      DESCRIPTION
              "The modem name used for this modem entry. If blank, this entry
               is currently unused."
      ::= { modemInfoEntry 3 }

  modemInitialisation OBJECT-TYPE
      SYNTAX      DisplayString(SIZE(0..30))
      MAX-ACCESS  read-write
      STATUS      current
      DESCRIPTION
              "The modem Initialisation string"
      ::= { modemInfoEntry 4 }


-- Services Info

  serviceStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {servicesInfo 1}

  serviceDHCP OBJECT-TYPE
      SYNTAX      OnOffValue
      MAX-ACCESS  read-write
      STATUS      current
      DESCRIPTION
               "Turn on/off the DHCP Service on the first ethernet interface."
      ::= {servicesInfo 2}

  serviceRouteD OBJECT-TYPE
      SYNTAX      OnOffValue
      MAX-ACCESS  read-write
      STATUS      current
      DESCRIPTION
               "RouteD Service"
      ::= {servicesInfo 3}

  serviceTelnetD OBJECT-TYPE
      SYNTAX      OnOffValue
      MAX-ACCESS  read-write
      STATUS      current
      DESCRIPTION
               "Turn on/off the TelnetD Service"
      ::= {servicesInfo 4}

  serviceSSHD OBJECT-TYPE
      SYNTAX      OnOffValue
      MAX-ACCESS  read-write
      STATUS      current
      DESCRIPTION
               "Turn on/off the SSHD Service"
      ::= {servicesInfo 5}

  serviceHTTPD OBJECT-TYPE
      SYNTAX      OnOffValue
      MAX-ACCESS  read-write
      STATUS      current
      DESCRIPTION
               "Turn on/off the HTTPD Service"
      ::= {servicesInfo 6}

  serviceSnmpD OBJECT-TYPE
      SYNTAX      OnOffValue
      MAX-ACCESS  read-write
      STATUS      current
      DESCRIPTION
               "Turn on/off the SnmpD Service"
      ::= {servicesInfo 7}

  serviceSPCD OBJECT-TYPE
      SYNTAX      OnOffValue
      MAX-ACCESS  read-write
      STATUS      current
      DESCRIPTION
               "Turn on/off the SPCD Service (TruePort)"
      ::= {servicesInfo 8}

  serviceSNTP OBJECT-TYPE
      SYNTAX      OnOffValue
      MAX-ACCESS  read-write
      STATUS      current
      DESCRIPTION
               "Turn on/off the SNTP Service"
      ::= {servicesInfo 9}

  serviceHTTPSD OBJECT-TYPE
      SYNTAX      OnOffValue
      MAX-ACCESS  read-write
      STATUS      current
      DESCRIPTION
               "Turn on/off the HTTPSD Service"
      ::= {servicesInfo 10}

  serviceSyslog OBJECT-TYPE
      SYNTAX      OnOffValue
      MAX-ACCESS  read-write
      STATUS      current
      DESCRIPTION
               "Turn on/off the Syslog Service"
      ::= {servicesInfo 11}

  serviceDeviceManagerD OBJECT-TYPE
      SYNTAX      OnOffValue
      MAX-ACCESS  read-write
      STATUS      current
      DESCRIPTION
               "Turn on/off the DeviceManagerD Service"
      ::= {servicesInfo 12}
	  
  serviceMODBUSD OBJECT-TYPE
      SYNTAX      OnOffValue
      MAX-ACCESS  read-write
      STATUS      current
      DESCRIPTION
               "Turn on/off the Modbus Gateway Service"
      ::= {servicesInfo 13}

  serviceSecondaryDHCP OBJECT-TYPE
      SYNTAX      OnOffValue
      MAX-ACCESS  read-write
      STATUS      current
      DESCRIPTION
               "Turn on/off the DHCP Service on the eth2 interface"
      ::= {servicesInfo 14}	  
      
  serviceIPSEC OBJECT-TYPE
      SYNTAX      OnOffValue
      MAX-ACCESS  read-write
      STATUS      current
      DESCRIPTION
               "Turn on/off the IPSEC Service"
      ::= {servicesInfo 15}	  
      
  serviceIncomingPings OBJECT-TYPE
      SYNTAX      OnOffValue
      MAX-ACCESS  read-write
      STATUS      current
      DESCRIPTION
               "Allow incoming ping requests"
      ::= {servicesInfo 16}	  
      
  serviceThirdDHCP OBJECT-TYPE
      SYNTAX      OnOffValue
      MAX-ACCESS  read-write
      STATUS      current
      DESCRIPTION
               "Turn on/off the DHCP Service on the eth3 interface"
      ::= {servicesInfo 17}	  
      
  
-- Trueport Info

  trueportStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {trueportInfo 1}

  trueport50 OBJECT-TYPE
      SYNTAX TrueportBaud
      MAX-ACCESS  read-write
      STATUS      current
      DESCRIPTION
               "Mapping for trueport baud rate 50"
      ::= {trueportInfo 2}

  trueport75 OBJECT-TYPE
      SYNTAX TrueportBaud
      MAX-ACCESS  read-write
      STATUS      current
      DESCRIPTION
               "Mapping for trueport baud rate 75"
      ::= {trueportInfo 3}

  trueport110 OBJECT-TYPE
      SYNTAX TrueportBaud
      MAX-ACCESS  read-write
      STATUS      current
      DESCRIPTION
               "Mapping for trueport baud rate 110"
      ::= {trueportInfo 4}

  trueport134 OBJECT-TYPE
      SYNTAX TrueportBaud
      MAX-ACCESS  read-write
      STATUS      current
      DESCRIPTION
               "Mapping for trueport baud rate 134"
      ::= {trueportInfo 5}

  trueport150 OBJECT-TYPE
      SYNTAX TrueportBaud
      MAX-ACCESS  read-write
      STATUS      current
      DESCRIPTION
               "Mapping for trueport baud rate 150"
      ::= {trueportInfo 6}

  trueport200 OBJECT-TYPE
      SYNTAX TrueportBaud
      MAX-ACCESS  read-write
      STATUS      current
      DESCRIPTION
               "Mapping for trueport baud rate 200"
      ::= {trueportInfo 7}

  trueport300 OBJECT-TYPE
      SYNTAX TrueportBaud
      MAX-ACCESS  read-write
      STATUS      current
      DESCRIPTION
               "Mapping for trueport baud rate 300"
      ::= {trueportInfo 8}

  trueport600 OBJECT-TYPE
      SYNTAX TrueportBaud
      MAX-ACCESS  read-write
      STATUS      current
      DESCRIPTION
               "Mapping for trueport baud rate 600"
      ::= {trueportInfo 9}

  trueport1200 OBJECT-TYPE
      SYNTAX TrueportBaud
      MAX-ACCESS  read-write
      STATUS      current
      DESCRIPTION
               "Mapping for trueport baud rate 1200"
      ::= {trueportInfo 10}

  trueport1800 OBJECT-TYPE
      SYNTAX TrueportBaud
      MAX-ACCESS  read-write
      STATUS      current
      DESCRIPTION
               "Mapping for trueport baud rate 1800"
      ::= {trueportInfo 11}

  trueport2400 OBJECT-TYPE
      SYNTAX TrueportBaud
      MAX-ACCESS  read-write
      STATUS      current
      DESCRIPTION
               "Mapping for trueport baud rate 2400"
      ::= {trueportInfo 12}

  trueport4800 OBJECT-TYPE
      SYNTAX TrueportBaud
      MAX-ACCESS  read-write
      STATUS      current
      DESCRIPTION
               "Mapping for trueport baud rate 4800"
      ::= {trueportInfo 13}

  trueport9600 OBJECT-TYPE
      SYNTAX TrueportBaud
      MAX-ACCESS  read-write
      STATUS      current
      DESCRIPTION
               "Mapping for trueport baud rate 9600"
      ::= {trueportInfo 14}

  trueport19200 OBJECT-TYPE
      SYNTAX TrueportBaud
      MAX-ACCESS  read-write
      STATUS      current
      DESCRIPTION
               "Mapping for trueport baud rate 19200"
      ::= {trueportInfo 15}

  trueport38400 OBJECT-TYPE
      SYNTAX TrueportBaud
      MAX-ACCESS  read-write
      STATUS      current
      DESCRIPTION
               "Mapping for trueport baud rate 38400"
      ::= {trueportInfo 16}

  trueportCustom50 OBJECT-TYPE
      SYNTAX      Integer32(50..230400)
      MAX-ACCESS  read-write
      STATUS      current
      DESCRIPTION
               "Mapping for trueport baud rate 50"
      ::= {trueportInfo 17}

  trueportCustom75 OBJECT-TYPE
      SYNTAX      Integer32(50..230400)
      MAX-ACCESS  read-write
      STATUS      current
      DESCRIPTION
               "custom mapping for trueport baud rate 75"
      ::= {trueportInfo 18}

  trueportCustom110 OBJECT-TYPE
      SYNTAX      Integer32(50..230400)
      MAX-ACCESS  read-write
      STATUS      current
      DESCRIPTION
               "custom mapping for trueport baud rate 110"
      ::= {trueportInfo 19}

  trueportCustom134 OBJECT-TYPE
      SYNTAX      Integer32(50..230400)
      MAX-ACCESS  read-write
      STATUS      current
      DESCRIPTION
               "custom mapping for trueport baud rate 134"
      ::= {trueportInfo 20}

  trueportCustom150 OBJECT-TYPE
      SYNTAX      Integer32(50..230400)
      MAX-ACCESS  read-write
      STATUS      current
      DESCRIPTION
               "custom mapping for trueport baud rate 150"
      ::= {trueportInfo 21}

  trueportCustom200 OBJECT-TYPE
      SYNTAX      Integer32(50..230400)
      MAX-ACCESS  read-write
      STATUS      current
      DESCRIPTION
               "custom mapping for trueport baud rate 200"
      ::= {trueportInfo 22}

  trueportCustom300 OBJECT-TYPE
      SYNTAX      Integer32(50..230400)
      MAX-ACCESS  read-write
      STATUS      current
      DESCRIPTION
               "custom mapping for trueport baud rate 300"
      ::= {trueportInfo 23}

  trueportCustom600 OBJECT-TYPE
      SYNTAX      Integer32(50..230400)
      MAX-ACCESS  read-write
      STATUS      current
      DESCRIPTION
               "custom mapping for trueport baud rate 600"
      ::= {trueportInfo 24}

  trueportCustom1200 OBJECT-TYPE
      SYNTAX      Integer32(50..230400)
      MAX-ACCESS  read-write
      STATUS      current
      DESCRIPTION
               "custom mapping for trueport baud rate 1200"
      ::= {trueportInfo 25}

  trueportCustom1800 OBJECT-TYPE
      SYNTAX      Integer32(50..230400)
      MAX-ACCESS  read-write
      STATUS      current
      DESCRIPTION
               "custom mapping for trueport baud rate 1800"
      ::= {trueportInfo 26}

  trueportCustom2400 OBJECT-TYPE
      SYNTAX      Integer32(50..230400)
      MAX-ACCESS  read-write
      STATUS      current
      DESCRIPTION
               "custom mapping for trueport baud rate 2400"
      ::= {trueportInfo 27}

  trueportCustom4800 OBJECT-TYPE
      SYNTAX      Integer32(50..230400)
      MAX-ACCESS  read-write
      STATUS      current
      DESCRIPTION
               "custom mapping for trueport baud rate 4800"
      ::= {trueportInfo 28}

  trueportCustom9600 OBJECT-TYPE
      SYNTAX      Integer32(50..230400)
      MAX-ACCESS  read-write
      STATUS      current
      DESCRIPTION
               "custom mapping for trueport baud rate 9600"
      ::= {trueportInfo 29}

  trueportCustom19200 OBJECT-TYPE
      SYNTAX      Integer32(50..230400)
      MAX-ACCESS  read-write
      STATUS      current
      DESCRIPTION
               "custom mapping for trueport baud rate 19200"
      ::= {trueportInfo 30}

  trueportCustom38400 OBJECT-TYPE
      SYNTAX      Integer32(50..230400)
      MAX-ACCESS  read-write
      STATUS      current
      DESCRIPTION
               "custom mapping for trueport baud rate 38400"
      ::= {trueportInfo 31}
-- Radius Info

  radiusStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {radiusInfo 1}

  radiusPrimaryAuthHost OBJECT-TYPE
      SYNTAX   DisplayString(SIZE(0..14))
      MAX-ACCESS    read-write
      STATUS        current
      DESCRIPTION
                "Primary Radius Authentication Host"
      ::= {radiusInfo 2}

  radiusSecondaryAuthHost OBJECT-TYPE
      SYNTAX   DisplayString(SIZE(0..14))
      MAX-ACCESS    read-write
      STATUS        current
      DESCRIPTION
                "Secondary Radius Authentication Host"
      ::= {radiusInfo 3}

  radiusAuthenticationPort OBJECT-TYPE
      SYNTAX   Integer32(0..65535)
      MAX-ACCESS    read-write
      STATUS        current
      DESCRIPTION
                "The port that the RADIUS host listens to for 
                 authentication requests. The default port is 1812."
      ::= {radiusInfo 4}

  radiusAccountingEnabled OBJECT-TYPE
      SYNTAX   OnOffValue
      MAX-ACCESS    read-write
      STATUS        current
      DESCRIPTION
                "Radius Accounting enabled"
      ::= {radiusInfo 5}

  radiusPrimaryAcctHost OBJECT-TYPE
      SYNTAX   DisplayString(SIZE(0..14))
      MAX-ACCESS    read-write
      STATUS        current
      DESCRIPTION
                "Name of the primary RADIUS authentication host."
      ::= {radiusInfo 6}

  radiusSecondaryAcctHost OBJECT-TYPE
      SYNTAX   DisplayString(SIZE(0..14))
      MAX-ACCESS    read-write
      STATUS        current
      DESCRIPTION
                "Name of the secondary RADIUS authentication host."
      ::= {radiusInfo 7}

  radiusAccountingPort OBJECT-TYPE
      SYNTAX   Integer32(0..65535)
      MAX-ACCESS    read-write
      STATUS        current
      DESCRIPTION
                "The port that the RADIUS host listens to for 
                 accounting requests. The default port is 1813."
      ::= {radiusInfo 8}

  radiusAcctAuth OBJECT-TYPE
      SYNTAX   OnOffValue
      MAX-ACCESS    read-write
      STATUS        current
      DESCRIPTION
                "Radius Accounting Authenticator enabled"
      ::= {radiusInfo 9}

  radiusRetryLimit OBJECT-TYPE
      SYNTAX   Integer32(0..255)
      MAX-ACCESS    read-write
      STATUS        current
      DESCRIPTION
                "The number of times the Device Server tries
                     to connect to the RADIUS server before erroring
                     out. Valid values are 0-255. The default is 5."
      ::= {radiusInfo 10}

  radiusTimeout OBJECT-TYPE
      SYNTAX   Integer32(1..255)
      MAX-ACCESS    read-write
      STATUS        current
      DESCRIPTION
                "The time, in seconds, that the Device Server waits
                     to receive a reply after sending out a request to
                     a RADIUS accounting or authentication host. If no
                     reply is received before the timeout period expires,
                     the Device Server will retry the same host up to and
                     including the number of retry attempts. Valid values
                     are 1-255. The default is 3 seconds."
      ::= {radiusInfo 11}
	  
  radiusNasIdentifier OBJECT-TYPE
      SYNTAX      DisplayString(SIZE(0..32))
      MAX-ACCESS  read-write
      STATUS      current
      DESCRIPTION
              "The NAS identifier name.
               To delete this , set this field to blank."
      ::= { radiusInfo 12 }
	  
  radiusNasIpAddress OBJECT-TYPE
      SYNTAX      OnOffValue
      MAX-ACCESS  read-write
      STATUS      current
      DESCRIPTION
              "When on, the NAS Identifier obtains ipv4 address automatically.
               Default is on."
      ::= { radiusInfo 13 }
	  
  radiusNasSpecifyIpAddress OBJECT-TYPE
      SYNTAX      IpAddress
      MAX-ACCESS  read-write
      STATUS      current
      DESCRIPTION
              "Specify the unique IPv4 address that NAS Identifier will use"
      ::= { radiusInfo 14}
	  
  radiusNasIpv6Address OBJECT-TYPE
      SYNTAX      OnOffValue
      MAX-ACCESS  read-write
      STATUS      current
      DESCRIPTION

              "When on, the NAS Identifier obtains ipv6 address automatically.
               Default is on."
      ::= { radiusInfo 15 }
	  
  radiusNasSpecifyIpv6Address OBJECT-TYPE
      SYNTAX      DisplayString
      MAX-ACCESS  read-write
      STATUS      current
      DESCRIPTION
              "Specify the unique IPv6 address that NAS Identifier will use"
      ::= { radiusInfo 16}

  radiusPrimaryAuthTunnel OBJECT-TYPE
      SYNTAX   DisplayString(SIZE(0..14))
      MAX-ACCESS    read-write
      STATUS        current
      DESCRIPTION
                "Primary Radius Authentication Tunnel"
      ::= {radiusInfo 17}

  radiusSecondaryAuthTunnel OBJECT-TYPE
      SYNTAX   DisplayString(SIZE(0..14))
      MAX-ACCESS    read-write
      STATUS        current
      DESCRIPTION
                "Secondary Radius Authentication Tunnel"
      ::= {radiusInfo 18}
  
  radiusPrimaryAcctTunnel OBJECT-TYPE
      SYNTAX   DisplayString(SIZE(0..14))
      MAX-ACCESS    read-write
      STATUS        current
      DESCRIPTION
                "Name of the primary RADIUS authentication tunnel."
      ::= {radiusInfo 19}

  radiusSecondaryAcctTunnel OBJECT-TYPE
      SYNTAX   DisplayString(SIZE(0..14))
      MAX-ACCESS    read-write
      STATUS        current
      DESCRIPTION
                "Name of the secondary RADIUS authentication tunnel."
      ::= {radiusInfo 20}
  
  
-- Kerberos Info

  kerberosStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {kerberosInfo 1}

  kerberosRealm OBJECT-TYPE
      SYNTAX   DisplayString(SIZE(0..32))
      MAX-ACCESS    read-write
      STATUS        current
      DESCRIPTION
                "The Kerberos realm is the Kerberos host domain name,
                     in upper-case letters."
      ::= {kerberosInfo 2}

  kerberosDomain OBJECT-TYPE
      SYNTAX   DisplayString(SIZE(0..32))
      MAX-ACCESS    read-write
      STATUS        current
      DESCRIPTION
                "The name of a host running the KDC (Key Distribution
                     Center) for the specified realm. The host name that
                     you specify must either be defined in the Device
                     Server's Host Table before the last reboot or be
                     resolved by DNS."
      ::= {kerberosInfo 3}

  kerberosPort OBJECT-TYPE
      SYNTAX   Integer32(0..65535)
      MAX-ACCESS    read-write
      STATUS        current
      DESCRIPTION
                "The port that the Kerberos server listens to for
                     authentication requests. If no port is specified,
                     the default port 88 is used."
      ::= {kerberosInfo 4}


-- ldap Info

  ldapStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {ldapInfo 1}

  ldapHost OBJECT-TYPE
      SYNTAX   DisplayString(SIZE(0..64))
      MAX-ACCESS    read-write
      STATUS        current
      DESCRIPTION
                "The name or IP address of the LDAP host. If you use
                     a host name, that host must either have been defined
                     in the Device Server's Host Table before the last
                     reboot or be resolved by DNS. If you are using TLS,
                     you must enter the same string you used to create
                     the LDAP certificate. "
      ::= {ldapInfo 2}

  ldapPort OBJECT-TYPE
      SYNTAX   Integer32(0..65535)
      MAX-ACCESS    read-write
      STATUS        current
      DESCRIPTION
                "The port that the LDAP host listens to for
                     authentication requests. The default port is 389."
      ::= {ldapInfo 3}

  ldapBase OBJECT-TYPE
      SYNTAX   DisplayString(SIZE(0..64))
      MAX-ACCESS    read-write
      STATUS        current
      DESCRIPTION
                "The domain component (dc) that is the starting
                     point for the search for user authentication."
      ::= {ldapInfo 4}

  ldapEnableTLS OBJECT-TYPE
      SYNTAX   OnOffValue
      MAX-ACCESS    read-write
      STATUS        current
      DESCRIPTION
                "Enables/disables the Transport Layer Security
                     (TLS) with the LDAP host."
      ::= {ldapInfo 5}

  ldapTLSPort OBJECT-TYPE
      SYNTAX   Integer32(0..65535)
      MAX-ACCESS    read-write
      STATUS        current
      DESCRIPTION
                "Specify the port number that LDAP will use
                     for TLS. The default is port 636."
      ::= {ldapInfo 6}

  ldapUID OBJECT-TYPE
      SYNTAX        DisplayString(SIZE(0..32))
      MAX-ACCESS    read-write
      STATUS        current
      DESCRIPTION
                "LDAP user attribute.
                 e.g.
                 uid                (OpenLDAP)
                 sAMAccountName     (Active Directory)
                 
                 The default is 'uid'."
      ::= {ldapInfo 7}
      
  ldapPasswordEncryption OBJECT-TYPE
      SYNTAX      INTEGER {
                     none(1),
                     md5(2)
                  }
      MAX-ACCESS    read-write
      STATUS        current
      DESCRIPTION
                "LDAP password encryption method."
      ::= {ldapInfo 8}
      
  ldapClientAuth OBJECT-TYPE
      SYNTAX   OnOffValue
      MAX-ACCESS    read-write
      STATUS        current
      DESCRIPTION
                "LDAP client authentication."
      ::= {ldapInfo 9}
      
  ldapClientName OBJECT-TYPE
      SYNTAX        DisplayString(SIZE(0..64))
      MAX-ACCESS    read-write
      STATUS        current
      DESCRIPTION
                "LDAP client name.  Identifies the unit to the LDAP server,
                 when client authentication is enabled."
      ::= {ldapInfo 10}

  ldapClientAppendBase OBJECT-TYPE
      SYNTAX   OnOffValue
      MAX-ACCESS    read-write
      STATUS        current
      DESCRIPTION
                "Append base to LDAP client name."
      ::= {ldapInfo 11}
      
  ldapClientPassword OBJECT-TYPE
      SYNTAX        DisplayString(SIZE(0..64))
      MAX-ACCESS    read-write
      STATUS        current
      DESCRIPTION
                "LDAP client password.  Identifies the unit to the LDAP server,
                 when client authentication is enabled."
      ::= {ldapInfo 12}
                     
  
  ldapHostTunnel OBJECT-TYPE
      SYNTAX   DisplayString(SIZE(0..14))
      MAX-ACCESS    read-write
      STATUS        current
      DESCRIPTION
                "The HTTP tunnel associated with the LDAP host. "
      ::= {ldapInfo 13}
  
-- TACACS Info

  tacacsStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {tacacsInfo 1}

  tacacsPrimaryHost OBJECT-TYPE
      SYNTAX   DisplayString(SIZE(0..14))
      MAX-ACCESS    read-write
      STATUS        current
      DESCRIPTION
                "The primary TACACS+ host that is used
                     for authentication."
      ::= {tacacsInfo 2}

  tacacsSecondaryHost OBJECT-TYPE
      SYNTAX   DisplayString(SIZE(0..14))
      MAX-ACCESS    read-write
      STATUS        current
      DESCRIPTION
                "The secondary TACACS+ host that is used
                     for authentication, should the primary
                     TACACS+ host fail to respond."
      ::= {tacacsInfo 3}

  tacacsPort OBJECT-TYPE
      SYNTAX   Integer32(0..65535)
      MAX-ACCESS    read-write
      STATUS        current
      DESCRIPTION
                "The port number that TACACS+ listens to
                     for authentication requests. The default
                     port number is 49."
      ::= {tacacsInfo 4}
      
  tacacsAccounting OBJECT-TYPE
      SYNTAX   OnOffValue
      MAX-ACCESS    read-write
      STATUS        current
      DESCRIPTION
                "Enable/Disable TACACS+ accounting"
      ::= {tacacsInfo 5}
      
  tacacsAccountingPrimaryHost OBJECT-TYPE
      SYNTAX   DisplayString(SIZE(0..14))
      MAX-ACCESS    read-write
      STATUS        current
      DESCRIPTION
                "The primary TACACS+ accounting host that is used
                     for."
      ::= {tacacsInfo 6}

  tacacsAccountingSecondaryHost OBJECT-TYPE
      SYNTAX   DisplayString(SIZE(0..14))
      MAX-ACCESS    read-write
      STATUS        current
      DESCRIPTION
                "The secondary TACACS+ accounting host that is used
                     for , should the primary TACACS+ host fail 
                     to respond."
      ::= {tacacsInfo 7}

  tacacsAccountingPort OBJECT-TYPE
      SYNTAX   Integer32(0..65535)
      MAX-ACCESS    read-write
      STATUS        current
      DESCRIPTION
                "The port number that TACACS+ listens to
                     for accounting requests. The default
                     port number is 49."
      ::= {tacacsInfo 8}

  tacacsAuthorization OBJECT-TYPE
      SYNTAX   OnOffValue
      MAX-ACCESS    read-write
      STATUS        current
      DESCRIPTION
                "Enable/Disable TACACS+ authorisation"
      ::= {tacacsInfo 9}
      
  tacacsAlternateServiceNames OBJECT-TYPE
      SYNTAX   OnOffValue
      MAX-ACCESS    read-write
      STATUS        current
      DESCRIPTION
                "Enable alternate service names for TACACS+."
      ::= {tacacsInfo 10}
 
  tacacsPrimaryTunnel OBJECT-TYPE
      SYNTAX   DisplayString(SIZE(0..14))
      MAX-ACCESS    read-write
      STATUS        current
      DESCRIPTION
                "The HTTP tunnel associated with the primary authentication server"
      ::= {tacacsInfo 11}

  tacacsSecondaryTunnel OBJECT-TYPE
      SYNTAX   DisplayString(SIZE(0..14))
      MAX-ACCESS    read-write
      STATUS        current
      DESCRIPTION
                "The HTTP tunnel associated with the secondary authentication server"
      ::= {tacacsInfo 12}
  
  tacacsAccountingPrimaryTunnel OBJECT-TYPE
      SYNTAX   DisplayString(SIZE(0..14))
      MAX-ACCESS    read-write
      STATUS        current
      DESCRIPTION
                "The HTTP tunnel associated with the primary accounting server"
      ::= {tacacsInfo 13}

  tacacsAccountingSecondaryTunnel OBJECT-TYPE
      SYNTAX   DisplayString(SIZE(0..14))
      MAX-ACCESS    read-write
      STATUS        current
      DESCRIPTION
                "The HTTP tunnel associated with the secondary accounting server"
      ::= {tacacsInfo 14}
  
-- Securid Info

  securidStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {securidInfo 1}

  securidMasterHost OBJECT-TYPE
      SYNTAX   DisplayString(SIZE(0..14))
      MAX-ACCESS    read-write
      STATUS        current
      DESCRIPTION
                "The first SecurID server that is tried for
                     user authentication."
      ::= {securidInfo 2}

  securidSlaveHost OBJECT-TYPE
      SYNTAX   DisplayString(SIZE(0..14))
      MAX-ACCESS    read-write
      STATUS        current
      DESCRIPTION
                "If the first SecurID server does not respond
                     to an authentication request, this is the next
                     SecurID server that is tried for user authentication."
      ::= {securidInfo 3}

  securidPort OBJECT-TYPE
      SYNTAX   Integer32(0..65535)
      MAX-ACCESS    read-write
      STATUS        current
      DESCRIPTION
                "The port number that SecurID listens to for
                     authentication requests. The default port number is 5500."
      ::= {securidInfo 4}

  securidType OBJECT-TYPE
      SYNTAX   INTEGER {
            des(1),
        sdi(2)
        }
      MAX-ACCESS    read-write
      STATUS        current
      DESCRIPTION
                "You can specify either SDI or DES encryption for SecurID
                     server communication. The default is SDI encryption."
      ::= {securidInfo 5}

  securidLegacy OBJECT-TYPE
      SYNTAX   YesNoValue
      MAX-ACCESS    read-write
      STATUS        current
      DESCRIPTION
                "If you are running SecurID 3.x or 4.x, you need to run
                     in Legacy Mode. If you are running SecurID 5.x or above,
                     do not select Legacy Mode."
      ::= {securidInfo 6}
  
  securidMasterTunnel OBJECT-TYPE
      SYNTAX   DisplayString(SIZE(0..14))
      MAX-ACCESS    read-write
      STATUS        current
      DESCRIPTION
                "HTTP tunnel associated with master host."
      ::= {securidInfo 7}

  securidSlaveTunnel OBJECT-TYPE
      SYNTAX   DisplayString(SIZE(0..14))
      MAX-ACCESS    read-write
      STATUS        current
      DESCRIPTION
                "HTTP tunnel associated with slave host."
      ::= {securidInfo 8}
  
-- NIS Info
  nisStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {nisInfo 1}

  nisDomain OBJECT-TYPE
      SYNTAX   DisplayString(SIZE(0..32))
      MAX-ACCESS    read-write
      STATUS        current
      DESCRIPTION
                "The NIS domain name."
      ::= {nisInfo 2}

  nisPrimaryHost OBJECT-TYPE
      SYNTAX   DisplayString(SIZE(0..14))
      MAX-ACCESS    read-write
      STATUS        current
      DESCRIPTION
                "The primary NIS host that is used for authentication."
      ::= {nisInfo 3}

  nisSecondaryHost OBJECT-TYPE
      SYNTAX   DisplayString(SIZE(0..14))
      MAX-ACCESS    read-write
      STATUS        current
      DESCRIPTION
                "The secondary NIS host that is used for authentication,
                     should the primary NIS host fail to respond."
      ::= {nisInfo 4}

  
  nisPrimaryTunnel OBJECT-TYPE
      SYNTAX   DisplayString(SIZE(0..14))
      MAX-ACCESS    read-write
      STATUS        current
      DESCRIPTION
                "The HTTP tunnel associated with the primary host."
      ::= {nisInfo 5}

  nisSecondaryTunnel OBJECT-TYPE
      SYNTAX   DisplayString(SIZE(0..14))
      MAX-ACCESS    read-write
      STATUS        current
      DESCRIPTION
                "The HTTP tunnel associated with the secondary host."
      ::= {nisInfo 6}

--******************************************************************************  
-- SSH Server Info

  sshServerStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {sshServerInfo 1}

 sshServerRSA OBJECT-TYPE
      SYNTAX   OnOffValue
      MAX-ACCESS    read-write
      STATUS        current
      DESCRIPTION
                "When a client SSH session requests RSA authentication,
                     the Device Server's SSH server will authenticate the
                     user via RSA."
      ::= {sshServerInfo 2}

  sshServerDSA OBJECT-TYPE
      SYNTAX   OnOffValue
      MAX-ACCESS    read-write
      STATUS        current
      DESCRIPTION
                "When a client SSH session requests DSA authentication,
                     the Device Server's SSH server will authenticate the
                     user via DSA"
      ::= {sshServerInfo 3}

  sshServerKeyboard OBJECT-TYPE
      SYNTAX   OnOffValue
      MAX-ACCESS    read-write
      STATUS        current
      DESCRIPTION
                "The user types in a password for authentication."
      ::= {sshServerInfo 4}

  sshServer3Des OBJECT-TYPE
      SYNTAX   OnOffValue
      MAX-ACCESS    read-write
      STATUS        current
      DESCRIPTION
                "The Device Server SSH server's 3DES encryption is
                     enabled/disabled."
      ::= {sshServerInfo 5}

  sshServerBlowfish OBJECT-TYPE
      SYNTAX   OnOffValue
      MAX-ACCESS    read-write
      STATUS        current
      DESCRIPTION
                "The Device Server SSH server's Blowfish encryption
                     is enabled/disabled."
      ::= {sshServerInfo 6}

  sshServerAES OBJECT-TYPE
      SYNTAX   OnOffValue
      MAX-ACCESS    read-write
      STATUS        current
      DESCRIPTION
                "The Device Server SSH server's AES-CBC encryption
                     is enabled/disabled"
      ::= {sshServerInfo 7}

  sshServerCAST OBJECT-TYPE
      SYNTAX   OnOffValue
      MAX-ACCESS    read-write
      STATUS        current
      DESCRIPTION
                "The Device Server SSH server's CAST encryption
                     is enabled/disabled"
      ::= {sshServerInfo 8}

  sshServerArcfour OBJECT-TYPE
      SYNTAX   OnOffValue
      MAX-ACCESS    read-write
      STATUS        current
      DESCRIPTION
                "The Device Server SSH server's Arcfour encryption
                     is enabled/disabled."
      ::= {sshServerInfo 9}

  sshServerVerbose OBJECT-TYPE
      SYNTAX   OnOffValue
      MAX-ACCESS    read-write
      STATUS        current
      DESCRIPTION
                "Displays debug messages on the terminal."
      ::= {sshServerInfo 10}

  sshServerCompression OBJECT-TYPE
      SYNTAX   OnOffValue
      MAX-ACCESS    read-write
      STATUS        current
      DESCRIPTION
                "Requests compression of all data. Compression is
                     desirable on modem lines and other slow connections,
                     but will only slow down things on fast networks."
      ::= {sshServerInfo 11}

  sshServerBreakString OBJECT-TYPE
      SYNTAX   DisplayString(SIZE(0..8))
      MAX-ACCESS    read-write
      STATUS        current
      DESCRIPTION
                "The break string used for inband SSH break signal
                     processing. A break signal is generated on a specific
                     serial port only when the server's break option is
                     enabled and the user currently connected using reverse
                     SSH has typed the break string exactly. The default is
                     set to ~break, where ~ is tilde; the break string can
                     be up to eight characters."
      ::= {sshServerInfo 12}

 sshServerSSH1 OBJECT-TYPE
      SYNTAX   OnOffValue
      MAX-ACCESS    read-write
      STATUS        current
      DESCRIPTION
                "Enable/Disable SSH-1 on the server."
      ::= {sshServerInfo 13}

  sshServerPassword OBJECT-TYPE
      SYNTAX   OnOffValue
      MAX-ACCESS    read-write
      STATUS        current
      DESCRIPTION
                "The user types in a password for authentication."
      ::= {sshServerInfo 14}

  sshServerLoginTimeout OBJECT-TYPE
      SYNTAX      INTEGER
      MAX-ACCESS  read-write
      STATUS      current
      DESCRIPTION
              "The number of seconds that the ssh session will wait to complete
                the login process. If the timer expires, then the ssh session 
                will be terminated."
      ::= { sshServerInfo 15 }

  sshServerAESctr OBJECT-TYPE
      SYNTAX   OnOffValue
      MAX-ACCESS    read-write
      STATUS        current
      DESCRIPTION
                "The Device Server SSH server's AES-CTR encryption
                     is enabled/disabled."
      ::= {sshServerInfo 16}

  sshServerAESgcm OBJECT-TYPE
      SYNTAX   OnOffValue
      MAX-ACCESS    read-write
      STATUS        current
      DESCRIPTION
                "The Device Server SSH server's AES-GCM encryption
                     is enabled/disabled."
      ::= {sshServerInfo 17}

  sshServerChaCha20Poly1305 OBJECT-TYPE
      SYNTAX   OnOffValue
      MAX-ACCESS    read-write
      STATUS        current
      DESCRIPTION
                "The Device Server SSH server's ChaCha20-Poly1305 encryption
                     is enabled/disabled."
      ::= {sshServerInfo 18}

  
--******************************************************************************      
-- Default user Info

  defUserStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { defUserInfo 1}

  defUserService OBJECT-TYPE
      SYNTAX      INTEGER {
        dsprompt(1),
        telnet(2),
        ssh(3),
        rlogin(4),
        slip(5),
        ppp(6),
        tcpclear(7),
        sslraw(8)
      }
      MAX-ACCESS  read-write
      STATUS      current
      DESCRIPTION
              "The type of service that the user will use:
               dsprompt, telnet, ssh, rlogin, slip, ppp, tcpclear
               or sslraw."
      ::= { defUserInfo 2 }

   defUserLanguage OBJECT-TYPE
      SYNTAX      INTEGER {
        english(1),
        custom(2)
      }
      MAX-ACCESS  read-write
      STATUS      current
      DESCRIPTION
              "You can specify whether a user will use English or
               Customlang as the language that appears in the Menu,
               CLI, or WebManager. The Device Server supports one custom
               language that must be downloaded to the Device Server;
               otherwise, Customlang defaults to English."
      ::= { defUserInfo 3 }

   defUserLevel OBJECT-TYPE
      SYNTAX      INTEGER {
        admin(1),
        normal(2),
        restricted(3),
        menu(4)
      }
      MAX-ACCESS  read-write
      STATUS      current
      DESCRIPTION
              "The access that a user is allowed:
               Admin-The admin level user has total access to the Device Server.
                     You can create more than one admin user account but we
                     recommend that you only have one. They can monitor and
                     configure the Device Server.
               Normal-The Normal level user has limited access to the Device Server.
                     Limited CLI commands and Menu access are available with the
                     ability to configure the user's own configuration settings.
               Restricted-The Restricted level user can only access predefined
                     sessions or access the Easy Port Access menu. Can only view or
                     monitor the Device Server using CLI commands to display
                     information about the Device Server.
               Menu-The menu level user will only be able to access predefined session
                     or access the Easy Port Access menu. The Easy Port Access allows
                     the user to connect to the accessible line without disconnecting
                     their initial connection to the Device Server. Does not have any
                     access to CLI commands."
      ::= { defUserInfo 4}

   defUserHotKeyPrefix OBJECT-TYPE
      SYNTAX      Hex8
      MAX-ACCESS  read-write
      STATUS      current
      DESCRIPTION
              "The prefix that a user types to control the current session. The default
               value is hex 01, which corresponds to Ctrl-a (^a) (hex value 02 would
               be Ctrl-b (^b), etc.):
               ^a number-To switch from one session to another, press ^a and then the
                     required session number. For example, ^a 2 would switch you to
                     session 2. Pressing ^a 0 will return you to the Device Server Menu.
               ^a n-Display the next session. The current session will remain active. The
                     lowest numbered active session will be displayed.
               ^a p-Display the previous session. The current session will remain active.
                     The highest numbered active session will be displayed.
               ^a m-To exit a session and return to the Device Server. You will be
                     returned to where you left off. The session will be left running.
               ^a l-(Lowercase L) Locks the line until the user unlocks it. The user is
                     prompted for a password (any password, excluding spaces) and locks
                     the line. Next, the user must retype the password to unlock the line.
               ^r-When you switch from a session back to the Menu, the screen may not be
                     redrawn correctly. If this happens, use this command to redraw it properly.
               The User Hotkey Prefix value overrides the Line Hotkey Prefix value. You can
               use the Hotkey Prefix keys to lock a line only when the line Lock parameter is On."
      ::= { defUserInfo 5}

   defUserPhoneNumber OBJECT-TYPE
      SYNTAX      DisplayString(SIZE(0..32))
      MAX-ACCESS  read-write
      STATUS      current
      DESCRIPTION
              "The phone number the Device Server will dial to callback the user
               (you must have set Callback to On). Enter the number without spaces."
      ::= { defUserInfo 6}

   defUserCallBack OBJECT-TYPE
      SYNTAX      OnOffValue
      MAX-ACCESS  read-write
      STATUS      current
      DESCRIPTION
              "When On, enter a phone number for the Device Server to call the user
               back (the Callback parameter is unrelated to the Line Dial parameter).
               Note: the Device Server will allow callback only when a user is
               authenticated. If the protocol over the link does not provide
               authentication, there will be no callback. Therefore, when the Line
               Service is set to PPP, you must use either PAP or CHAP, because these
               protocols provide authentication. The default is Off. The Device Server
               supports another type of callback, Roaming Callback, which is
               configurable when the Line Service is set to PPP."
      ::= { defUserInfo 7}

   defUserIdleTimer OBJECT-TYPE
      SYNTAX      Integer32(0..4294967)
      MAX-ACCESS  read-write
      STATUS      current
      DESCRIPTION
              "The amount of time, in seconds, that the Idle Timer will run. Use this timer
               to close a connection because of inactivity. When the Idle Timer expires, because
               there has been no exchange of data within the specified time, the Device Server
               will close the connection. The default value is 0 (zero), meaning that the
               Idle Timer will not expire (the connection is open permanently). The maximum value
               is 4294967 seconds. The User Idle Timer will override the Line Idle Timer, with
               the exception of reverse Telnet sessions."
      ::= { defUserInfo 8}

   defUserSessionTimer OBJECT-TYPE
      SYNTAX      Integer32(0..4294967)
      MAX-ACCESS  read-write
      STATUS      current
      DESCRIPTION
              "Enter a time, in seconds, for which the Session Timer will run. Use this
               timer to forcibly close the session (connection). When the Session Timer
               expires, the Device Server will end the connection. The default value is
               0 seconds so the port will never timeout. The maximum value is 4294967
               seconds (about 49 days)."
      ::= { defUserInfo 9}

   defUserIpHost OBJECT-TYPE
      SYNTAX      Ipv4v6Address
      MAX-ACCESS  read-write
      STATUS      current
      DESCRIPTION
              "When the User Service is set to Telnet, TCP_clear or SSL_RAW, the target
               host IP address. If 255.255.255.255 is specified in the configuration,
               the user will be prompted for an IP address or hostname. If no IP
               address is specified, the Host IP value in the Default User configuration
               will be used. The default is 0.0.0.0."
      ::= { defUserInfo 10}

   defUserTelnetPort OBJECT-TYPE
      SYNTAX      Integer32(0..65535)
      MAX-ACCESS  read-write
      STATUS      current
      DESCRIPTION
              "The port number the target host is listening on for
               incoming connections. Default is 23."
      ::= { defUserInfo 11}

   defUserSSHPort OBJECT-TYPE
      SYNTAX      Integer32(0..65535)
      MAX-ACCESS  read-write
      STATUS      current
      DESCRIPTION
              "userSSHPort"
      ::= { defUserInfo 12}

   defUserTcpClearPort OBJECT-TYPE
      SYNTAX      Integer32(0..65535)
      MAX-ACCESS  read-write
      STATUS      current
      DESCRIPTION
              "The port number for the TCP-Clear or SSL-Raw session."
      ::= { defUserInfo 13}

   defUserFramedIp OBJECT-TYPE
      SYNTAX      IpAddress
      MAX-ACCESS  read-write
      STATUS      current
      DESCRIPTION
              "Used for User Service PPP or SLIP, sets the IP address of the
               remote user. Enter the address in dot decimal notation as follows:
               255.255.255.254 (default)-The Device Server will use the Remote
                  IP Address set in the PPP settings for the line.
               255.255.255.255-When the User Service is PPP, the Device Server will
                  allow the remote machine to specify its IP address (overriding
                  the IP address negotiation value configured in the PPP settings).
               255.255.255.255-When the User Service is SLIP, the Device Server will
                  use the Remote IP Address set for the line (no negotiation).
               n.n.n.n-(where n is a number) Enter the IP address of your choice.
                  This IP address will then be used in preference to the Remote IP
                  Address set for a line."
      ::= { defUserInfo 14}

   defUserSubnetBits OBJECT-TYPE
      SYNTAX      Integer32(0..32)
      MAX-ACCESS  read-write
      STATUS      current
      DESCRIPTION
              "(IPv4 only) If the remote user is on a subnet, enter the number of
               bits in the subnet mask. For example, a subnet mask of 255.255.0.0
               has 16 subnet/prefix bits."
      ::= { defUserInfo 15}

   defUserIpv6InterfaceId OBJECT-TYPE
      SYNTAX      Ipv6InterfaceId
      MAX-ACCESS  read-write
      STATUS      current
      DESCRIPTION
              "Used for User Service PPP, sets the IP address of the remote user.
               Enter the address in IPv6 format. The first 64 bits of the Interface
               Identifier must be zero, therefore, ::abcd:abcd:abcd:abcd is the
               expected format."
      ::= { defUserInfo 16}

   defUserFramedMtu OBJECT-TYPE
      SYNTAX      Integer32(64..1500)
      MAX-ACCESS  read-write
      STATUS      current
      DESCRIPTION
              "Used for User Service PPP or SLIP, specifies the maximum size of
               packets, in bytes, being transferred across the link. On noisy
               links it might be preferable to fragment large packets being
               transferred over the link, since there will be quicker recovery
               from errors. Depending on whether you have selected a User Service
               of SLIP or PPP, details are as follows:
               PPP-Framed MTU will be the maximum size of packets that the Device
                  Server port will accept. This value is negotiated between the
                  two ends of the link. The valid range is 64-1500. The default
                  is 1500 bytes.
               SLIP-Framed MTU will be the maximum size of packets being sent by
                  the Device Server. The Device Server will send SLIP packets in
                  the range 256-1006 bytes. The default value is 256 bytes.
               The Framed MTU value will be used in preference to the MTU/MRU values
               set for a Line."
      ::= { defUserInfo 17}

   defUserFramedCompression OBJECT-TYPE
      SYNTAX      OnOffValue
      MAX-ACCESS  read-write
      STATUS      current
      DESCRIPTION
              "Used for User Service PPP or SLIP, determines whether Van Jacobsen
               Compression is used on the link. VJ compression is a means of reducing
               the standard TCP/IP header from 40 octets to approximately 5 octets.
               This gives a significant performance improvement, particularly when
               interactive applications are being used. For example, when the user is
               typing, a single character can be passed over the link with a 40 octet
               header attached. VJ Compression has little effect on other types of links,
               such as ftp, where the packets are much larger. The Framed Compression
               value will be used in preference to the VJ Compression value set for a
               Line. The default is Off."
      ::= { defUserInfo 18}

   defUserRouting OBJECT-TYPE
      SYNTAX      INTEGER {
        none(1),
        send(2),
        listen(3),
        sendAndListen(4)
      }
      MAX-ACCESS  read-write
      STATUS      current
      DESCRIPTION
              "Determines the routing mode used for RIP packets on the PPP and SLIP
               interfaces. Values are:
               None-RIP packets are neither received nor sent by the Device Server.
               Send-RIP packets can only be sent by the Device Server.
               Listen-RIP packets can only be received by the Device Server.
               Send and Listen-RIP packets are sent and received by the Device Server."
      ::= { defUserInfo 19}
      
    defUserAllowAccessClusterPorts OBJECT-TYPE
      SYNTAX      OnOffValue
      MAX-ACCESS  read-write
      STATUS      current
      DESCRIPTION
              "Allow/disallow the user to access to clustering ports."
      ::= { defUserInfo 20 }

    defUserHost OBJECT-TYPE
      SYNTAX      DisplayString (SIZE(0..14))
      MAX-ACCESS  read-write
      STATUS      current
      DESCRIPTION
              "The name of the  host."
      ::= { defUserInfo 21}

-- Default User Port Access Table

  defUserPortAccessTable OBJECT-TYPE
      SYNTAX      SEQUENCE OF DefUserPortAccessEntry
      MAX-ACCESS  not-accessible
      STATUS      current
      DESCRIPTION
              "The port access info table for user."
      ::= { defUserInfo 22 }

  defUserPortAccessEntry OBJECT-TYPE
      SYNTAX      DefUserPortAccessEntry
      MAX-ACCESS  not-accessible
      STATUS      current
      DESCRIPTION
              "An entry in the portAccessTable, each relating to a user's
               access privileges for a serial port."
      INDEX   { defUserPortAccessPortIndex }
      ::= { defUserPortAccessTable 1 }

  DefUserPortAccessEntry ::=
      SEQUENCE {
        defUserPortAccessPortIndex	PortNumber,
        defUserPortAccessStatus     ContainerStatus,
        defUserPortRWAccessAllowed  YesNoValue,
        defUserPortRIAccessAllowed  YesNoValue,
        defUserPortROAccessAllowed  YesNoValue
      }

  defUserPortAccessPortIndex OBJECT-TYPE
      SYNTAX      PortNumber
      MAX-ACCESS  not-accessible
      STATUS      current
      DESCRIPTION
              "The port number that user access applies to."
      ::= { defUserPortAccessEntry 1 }

  defUserPortAccessStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { defUserPortAccessEntry 2 }

  defUserPortRWAccessAllowed OBJECT-TYPE
      SYNTAX      YesNoValue
      MAX-ACCESS  read-write
      STATUS      current
      DESCRIPTION
              "Enable or disable the user's read write access to the port."
      ::= { defUserPortAccessEntry 3 }

  defUserPortRIAccessAllowed OBJECT-TYPE
      SYNTAX      YesNoValue
      MAX-ACCESS  read-write
      STATUS      current
      DESCRIPTION
              "Enable or disable the user's read input access to the port."
      ::= { defUserPortAccessEntry 4 }

  defUserPortROAccessAllowed OBJECT-TYPE
      SYNTAX      YesNoValue
      MAX-ACCESS  read-write
      STATUS      current
      DESCRIPTION
              "Enable or disable the user's read output access to the port."
      ::= { defUserPortAccessEntry 5 }

-- SNMP Info

   snmpStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { snmpInfo 1}

   snmpContact OBJECT-TYPE
      SYNTAX      DisplayString(SIZE(0..14))
      MAX-ACCESS  read-write
      STATUS      current
      DESCRIPTION
              "The name and contract information of the person who manages this SMNP node."
      ::= { snmpInfo 2}

   snmpLocation OBJECT-TYPE
      SYNTAX      DisplayString(SIZE(0..32))
      MAX-ACCESS  read-write
      STATUS      current
      DESCRIPTION
              "The physical location of the SNMP node."
      ::= { snmpInfo 3}

   snmpReadOnlyUser OBJECT-TYPE
      SYNTAX      DisplayString(SIZE(0..16))
      MAX-ACCESS  read-write
      STATUS      current
      DESCRIPTION
              "(SNMP version 3) Specified user can only view SNMP variables."
      ::= { snmpInfo 4}

   snmpReadWriteUser OBJECT-TYPE
      SYNTAX      DisplayString(SIZE(0..16))
      MAX-ACCESS  read-write
      STATUS      current
      DESCRIPTION
              "(SNMP version 3) Specified user can view and edit SNMP variables."
      ::= { snmpInfo 5}

-- SNMP Community Info

   snmpCommunityTable OBJECT-TYPE
      SYNTAX      SEQUENCE OF SnmpCommunityEntry
      MAX-ACCESS  not-accessible
      STATUS      current
      DESCRIPTION
              "snmpCommunityTable"
      ::= { snmpInfo 6}

   snmpCommunityEntry OBJECT-TYPE
      SYNTAX      SnmpCommunityEntry
      MAX-ACCESS  not-accessible
      STATUS      current
      DESCRIPTION
               "snmpCommunityEntry"
      INDEX   { snmpCommunityIndex }
      ::= { snmpCommunityTable 1 }

   SnmpCommunityEntry ::=
      SEQUENCE {
        snmpCommunityIndex              GenericTableIndex,
        snmpCommunityStatus              ContainerStatus,
        snmpCommunityName              DisplayString,
        snmpCommunityIpAddress              Ipv4v6Address,
        snmpCommunityPermission              INTEGER
              }

   snmpCommunityIndex OBJECT-TYPE
      SYNTAX      GenericTableIndex
      MAX-ACCESS  not-accessible
      STATUS      current
      DESCRIPTION
              "snmpCommunityIndex"
      ::= { snmpCommunityEntry 1}

  snmpCommunityStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { snmpCommunityEntry 2}

   snmpCommunityName OBJECT-TYPE
      SYNTAX      DisplayString(SIZE(0..14))
      MAX-ACCESS  read-write
      STATUS      current
      DESCRIPTION
              "A name that will be sent to the Device Server from an SNMP
               manager. This name will define the permissions of the manager."
      ::= { snmpCommunityEntry 3}

   snmpCommunityIpAddress OBJECT-TYPE
      SYNTAX      Ipv4v6Address
      MAX-ACCESS  read-write
      STATUS      current
      DESCRIPTION
              "The IP address of the SNMP manager that will send requests to
               the Device Server. If the address is 0.0.0.0, any SNMP manager
               with the Community Name can access the Device Server."
      ::= { snmpCommunityEntry 4}

   snmpCommunityPermission OBJECT-TYPE
      SYNTAX      INTEGER {
        none(1),
        readonly(2),
        readwrite(3)
      }
      MAX-ACCESS  read-write
      STATUS      current
      DESCRIPTION
              "Permits the Device Server to respond to SNMP requests by:
               None-There is no response to requests from SNMP.
               Readonly-Responds only to Read requests from SNMP.
               Readwrite-Responds to both Read and Write requests from SNMP."
      ::= { snmpCommunityEntry 5}

-- SNMP Trap Table

   snmpTrapTable OBJECT-TYPE
      SYNTAX      SEQUENCE OF SnmpTrapEntry
      MAX-ACCESS  not-accessible
      STATUS      current
      DESCRIPTION
              "snmpTrapTable"
      ::= { snmpInfo 7}

   snmpTrapEntry OBJECT-TYPE
      SYNTAX      SnmpTrapEntry
      MAX-ACCESS  not-accessible
      STATUS      current
      DESCRIPTION
               "snmpTrapEntry"
      INDEX   { snmpTrapIndex }
      ::= { snmpTrapTable 1 }

   SnmpTrapEntry ::=
      SEQUENCE {
      	  		snmpTrapIndex        		GenericTableIndex,
      	  		snmpTrapStatus           	ContainerStatus,
      	  		snmpTrapName             	DisplayString,
      	  		snmpTrapIpAddress		Ipv4v6Address,
      	  		snmpTrapTunnelName       	DisplayString,
      	  		snmpTrapVersion          	INTEGER,
      	  		snmpTrapType             	INTEGER,
      	  		snmpTrapEnable 			INTEGER
              }

   snmpTrapIndex OBJECT-TYPE
      SYNTAX      GenericTableIndex
      MAX-ACCESS  not-accessible
      STATUS      current
      DESCRIPTION
              "snmpTrapIndex"
      ::= { snmpTrapEntry 1}

  snmpTrapStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { snmpTrapEntry 2}

   snmpTrapName OBJECT-TYPE
      SYNTAX      DisplayString(SIZE(0..14))
      MAX-ACCESS  read-write
      STATUS      current
      DESCRIPTION
              "An arbitrary trap community name."
      ::= { snmpTrapEntry 3}

   snmpTrapIpAddress OBJECT-TYPE
      SYNTAX      Ipv4v6Address
      MAX-ACCESS  read-write
      STATUS      current
      DESCRIPTION
              "Defines the hosts (by IP address) that will receive
               trap messages generated by the Device Server. Up to four
               trap hosts can be defined."
      ::= { snmpTrapEntry 4}

   snmpTrapTunnelName OBJECT-TYPE
      SYNTAX      DisplayString(SIZE(0..14))
      MAX-ACCESS  read-write
      STATUS      current
      DESCRIPTION
              "The name of the HTTP tunnel associated with this service."
      ::= { snmpTrapEntry 5 }
  
   snmpTrapVersion OBJECT-TYPE
      SYNTAX      INTEGER {
        v1(1),
        v2c(2),
        v3(3)
      }
      MAX-ACCESS  read-write
      STATUS      current
      DESCRIPTION
              "Set trap version."
      ::= {snmpTrapEntry 6 } 
      
   snmpTrapType OBJECT-TYPE
      SYNTAX      INTEGER {
        trap(1),
        inform(2)
      }
      MAX-ACCESS  read-write
      STATUS      current
      DESCRIPTION
              "Set trap type. Inform is only valid for v2c or v3."
      ::= {snmpTrapEntry 7 } 
      
   snmpTrapEnable OBJECT-TYPE
      SYNTAX      INTEGER {
        disabled(1),
        enabled(2)
      }
      MAX-ACCESS  read-write
      STATUS      current
      DESCRIPTION
              "Set trap enabled."
      ::= {snmpTrapEntry 8 } 

--******************************************************************************  
   snmpReadOnlySecurityLevel OBJECT-TYPE
      SYNTAX      INTEGER {
        none(1),
        authNoPriv(2),
        authPriv(3)
      }
      MAX-ACCESS  read-write
      STATUS      current
      DESCRIPTION
              "Set read only user security level."
      ::= {snmpInfo 8 } 
      
   snmpReadOnlyAuthAlgorithm OBJECT-TYPE
      SYNTAX      INTEGER {
        md5(1),
        sha(2)
      }
      MAX-ACCESS  read-write
      STATUS      current
      DESCRIPTION
              "Set read only user authentication method."
      ::= {snmpInfo 9 }   

      
     snmpReadOnlyAuthPasswd OBJECT-TYPE
      SYNTAX      DisplayString(SIZE(0..128))
      MAX-ACCESS  read-write
      STATUS      current
      DESCRIPTION
              "set read only user authentication password."
      ::= { snmpInfo 10}
      
    snmpReadOnlyPrivacyAlgorithm OBJECT-TYPE
      SYNTAX      INTEGER {
        des(1),
        aes(2)
      }
      MAX-ACCESS  read-write
      STATUS      current
      DESCRIPTION
              "Set read only user privacy algorithm."
      ::= {snmpInfo 11 }   
      
     snmpReadOnlyPrivacyPasswd OBJECT-TYPE
      SYNTAX      DisplayString(SIZE(0..128))
      MAX-ACCESS  read-write
      STATUS      current
      DESCRIPTION
              "set read only user privacy password."
      ::= { snmpInfo 12}

     snmpReadWriteSecurityLevel OBJECT-TYPE
      SYNTAX      INTEGER {
        none(1),
        authNoPriv(2),
        authPriv(3)
      }
      MAX-ACCESS  read-write
      STATUS      current
      DESCRIPTION
              "Set read write user security level."
      ::= {snmpInfo 13 } 
      
    snmpReadWriteAuthAlgorithm OBJECT-TYPE
      SYNTAX      INTEGER {
        md5(1),
        sha(2)
      }
      MAX-ACCESS  read-write
      STATUS      current
      DESCRIPTION
              "Set read write user authentication method."
      ::= {snmpInfo 14 }   
      
     snmpReadWriteAuthPasswd OBJECT-TYPE
      SYNTAX      DisplayString(SIZE(0..128))
      MAX-ACCESS  read-write
      STATUS      current
      DESCRIPTION
              "set read write user authentication password."
      ::= { snmpInfo 15}
      
    snmpReadWritePrivacyAlgorithm OBJECT-TYPE
      SYNTAX      INTEGER {
        des(1),
        aes(2)
      }
      MAX-ACCESS  read-write
      STATUS      current
      DESCRIPTION
              "Set read write user privacy algorithm."
      ::= {snmpInfo 16 }   
      
     snmpReadWritePrivacyPasswd OBJECT-TYPE
      SYNTAX      DisplayString(SIZE(0..128))
      MAX-ACCESS  read-write
      STATUS      current
      DESCRIPTION
              "set read write user privacy password."
      ::= { snmpInfo 17}
      
    snmpTrapUser OBJECT-TYPE
      SYNTAX      DisplayString(SIZE(0..16))
      MAX-ACCESS  read-write
      STATUS      current
      DESCRIPTION
              "(SNMP version 3) Specified user for sending traps."
      ::= { snmpInfo 18}

     snmpTrapSecurityLevel OBJECT-TYPE
      SYNTAX      INTEGER {
        none(1),
        authNoPriv(2),
        authPriv(3)
      }
      MAX-ACCESS  read-write
      STATUS      current
      DESCRIPTION
              "Set trap user security level."
      ::= {snmpInfo 19 } 
      
    snmpTrapAuthAlgorithm OBJECT-TYPE
      SYNTAX      INTEGER {
        md5(1),
        sha(2)
      }
      MAX-ACCESS  read-write
      STATUS      current
      DESCRIPTION
              "Set trap user authentication method."
      ::= {snmpInfo 20 }   
      
     snmpTrapAuthPasswd OBJECT-TYPE
      SYNTAX      DisplayString(SIZE(0..128))
      MAX-ACCESS  read-write
      STATUS      current
      DESCRIPTION
              "set trap user authentication password."
      ::= { snmpInfo 21}
      
    snmpTrapPrivacyAlgorithm OBJECT-TYPE
      SYNTAX      INTEGER {
        des(1),
        aes(2)
      }
      MAX-ACCESS  read-write
      STATUS      current
      DESCRIPTION
              "Set trap user privacy algorithm."
      ::= {snmpInfo 22 }   
      
     snmpTrapPrivacyPasswd OBJECT-TYPE
      SYNTAX      DisplayString(SIZE(0..128))
      MAX-ACCESS  read-write
      STATUS      current
      DESCRIPTION
              "set trap user privacy password."
      ::= { snmpInfo 23}
      
     snmpEngineIdString OBJECT-TYPE
      SYNTAX      DisplayString(SIZE(0..128))
      MAX-ACCESS  read-write
      STATUS      current
      DESCRIPTION
              "set the string to use to create the engine ID."
      ::= { snmpInfo 24}
      
     snmpEngineId OBJECT-TYPE
      SYNTAX      DisplayString(SIZE(0..128))
      MAX-ACCESS  read-only
      STATUS      current
      DESCRIPTION
              "Displays the current engine ID."
      ::= { snmpInfo 25}
      
    snmpInformTimeout OBJECT-TYPE
      SYNTAX      Integer32(0..231)
      MAX-ACCESS  read-write
      STATUS      current
      DESCRIPTION
              "Set Inform timeout in seconds."
      ::= {snmpInfo 26 }   
      
    snmpInformRetries OBJECT-TYPE
      SYNTAX      Integer32(0..231)
      MAX-ACCESS  read-write
      STATUS      current
      DESCRIPTION
              "Set Inform retries in seconds."
      ::= {snmpInfo 27 }   
      
-- DNS Info

   dnsTable OBJECT-TYPE
      SYNTAX      SEQUENCE OF DnsEntry
      MAX-ACCESS  not-accessible
      STATUS      current
      DESCRIPTION
              "dnsTable"
      ::= { dnsInfo 1}

   dnsEntry OBJECT-TYPE
      SYNTAX      DnsEntry
      MAX-ACCESS  not-accessible
      STATUS      current
      DESCRIPTION
               "dnsEntry"
      INDEX   { dnsIndex }
      ::= { dnsTable 1 }

   DnsEntry ::=
      SEQUENCE {
        dnsIndex            GenericTableIndex,
        dnsStatus            ContainerStatus,
        dnsIpAddress            Ipv4v6Address,
        dnsActive            OnOffValue
          }

   dnsIndex OBJECT-TYPE
      SYNTAX      GenericTableIndex
      MAX-ACCESS  not-accessible
      STATUS      current
      DESCRIPTION
              "dnsIndex"
      ::= { dnsEntry 1}

   dnsStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { dnsEntry 2 }

   dnsIpAddress OBJECT-TYPE
      SYNTAX      Ipv4v6Address
      MAX-ACCESS  read-write
      STATUS      current
      DESCRIPTION
              "You can specify the IP addresses for up to two DNS
               (Domain Name Servers) hosts in your network. The first
               DNS entry in the list is the primary DNS and the second
               DNS entry is the secondary server."
      ::= { dnsEntry 3}

   dnsActive OBJECT-TYPE
      SYNTAX      OnOffValue
      MAX-ACCESS  read-write
      STATUS      current
      DESCRIPTION
              "Activates/deactivates a DNS entry."
      ::= { dnsEntry 4}


-- WINS Info

   winsTable OBJECT-TYPE
      SYNTAX      SEQUENCE OF WinsEntry
      MAX-ACCESS  not-accessible
      STATUS      current
      DESCRIPTION
              "winsTable"
      ::= { winsInfo 1}

   winsEntry OBJECT-TYPE
      SYNTAX      WinsEntry
      MAX-ACCESS  not-accessible
      STATUS      current
      DESCRIPTION
               "winsEntry"
      INDEX   { winsIndex }
      ::= { winsTable 1 }

   WinsEntry ::=
      SEQUENCE {
        winsIndex            GenericTableIndex,
        winsStatus            ContainerStatus,
        winsIpAddress            Ipv4v6Address,
        winsActive            OnOffValue
          }

   winsIndex OBJECT-TYPE
      SYNTAX      GenericTableIndex
      MAX-ACCESS  not-accessible
      STATUS      current
      DESCRIPTION
              "winsIndex"
      ::= { winsEntry 1}

   winsStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { winsEntry 2}

   winsIpAddress OBJECT-TYPE
      SYNTAX      Ipv4v6Address
      MAX-ACCESS  read-write
      STATUS      current
      DESCRIPTION
              "You can specify the IP addresses for up to two WINS
               (Windows Internet Naming Service) hosts in your network.
               The first WINS entry in the list is the primary WINS server
               and the second WINS entry is the secondary server."
      ::= { winsEntry 3}

   winsActive OBJECT-TYPE
      SYNTAX      OnOffValue
      MAX-ACCESS  read-write
      STATUS      current
      DESCRIPTION
              "Activates/deactivates a WINS entry."
      ::= { winsEntry 4}

-- Gateway Info

   gatewayTable OBJECT-TYPE
      SYNTAX      SEQUENCE OF GatewayEntry
      MAX-ACCESS  not-accessible
      STATUS      current
      DESCRIPTION
              "gatewayTable"
      ::= { gatewayInfo 1}

   gatewayEntry OBJECT-TYPE
      SYNTAX      GatewayEntry
      MAX-ACCESS  not-accessible
      STATUS      current
      DESCRIPTION
               "gatewayEntry"
      INDEX   { gatewayIndex }
      ::= { gatewayTable 1 }

   GatewayEntry ::=
      SEQUENCE {
        gatewayIndex              GenericTableIndex,
        gatewayStatus            ContainerStatus,
        gatewayHost            DisplayString,
        gatewayType            INTEGER,
        gatewayIpAddress            Ipv4v6Address,
        gatewaySubnetBits            Integer32,
        gatewayInterface            DisplayString
          }

   gatewayIndex OBJECT-TYPE
      SYNTAX      GenericTableIndex
      MAX-ACCESS  not-accessible
      STATUS      current
      DESCRIPTION
              "gatewayIndex"
      ::= { gatewayEntry 1}

   gatewayStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { gatewayEntry 2}

   gatewayHost OBJECT-TYPE
      SYNTAX      DisplayString(SIZE(0..14))
      MAX-ACCESS  read-write
      STATUS      current
      DESCRIPTION
              "You can specify up to twenty hosts to act as gateways
               in your network. Each gateway host must be defined in
               the Device Server host table."
      ::= { gatewayEntry 3}

   gatewayType OBJECT-TYPE
      SYNTAX      INTEGER {
        host(1),
        network(2),
        default(3)
      }
      MAX-ACCESS  read-write
      STATUS      current
      DESCRIPTION
              "Specify the type of gateway:
               Default-A gateway which provides general access beyond
                    your local network.
               Host-A gateway reserved for accessing a specific host
                    external to your local network.
               Network-A gateway reserved for accessing a specific
                    network external to your local network."
      ::= { gatewayEntry 4}

   gatewayIpAddress OBJECT-TYPE
      SYNTAX      Ipv4v6Address
      MAX-ACCESS  read-write
      STATUS      current
      DESCRIPTION
              "When the gateway is a Host or Network gateway, you must
               specify the IP address of the target host machine/network."
      ::= { gatewayEntry 5}

   gatewaySubnetBits OBJECT-TYPE
      SYNTAX      Integer32(0..128)
      MAX-ACCESS  read-write
      STATUS      current
      DESCRIPTION
              "When the gateway is a Network gateway, you must specify the
               subnet/prefix bits for that network. If the IP address is IPv4,
               then the Subnet/Prefix Bits range is 0-32. If the IP address
               is IPv6, then the Subnet/Prefix Bits range is 0-128."
      ::= { gatewayEntry 6}

   gatewayInterface OBJECT-TYPE
      SYNTAX      DisplayString(SIZE(0..20))
      MAX-ACCESS  read-write
      STATUS      current
      DESCRIPTION
              "The interface that the device server is going to use to access the 
               Remote Host. The list is comprised of the Ethernet interface(s)
               and serial ports configured for the Remote Access (PPP) or 
               Remote Access (SLIP) profiles. This string must be the actual
               name of the PPP/SLIP serial port, serial_port_x (where x=number) if no
               name is specified or the IPv6 tunnel name or ipv6_tunnelx (where 
               x=tunnel number)."
      ::= { gatewayEntry 7}

-- Syslog Info

  syslogStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { syslogInfo 1}

   syslogPrimaryHost OBJECT-TYPE
      SYNTAX      DisplayString(SIZE(0..14))
      MAX-ACCESS  read-write
      STATUS      current
      DESCRIPTION
              "The first preconfigured host that the Device Server will attempt
               to send system log messages to; messages will be displayed on the
               host's monitor."
      ::= { syslogInfo 2}

   syslogSecondaryHost OBJECT-TYPE
      SYNTAX      DisplayString(SIZE(0..14))
      MAX-ACCESS  read-write
      STATUS      current
      DESCRIPTION
              "If the Device Server cannot communicate with the primary host,
               then the Device Server will attempt to send system log messages to
               this preconfigured host; messages will be displayed on the host's monitor."
      ::= { syslogInfo 3}
  
    syslogLevel OBJECT-TYPE
      SYNTAX      INTEGER {
        emergency(1),
        alert(2),
        critical(3),
        error(4),
        warning(5),
        notice(6),
        informational(7),
        debug(8)
      }
      MAX-ACCESS  read-write
      STATUS      current
      DESCRIPTION
              "Choose the event level that triggers a syslog entry:
               Emergency, Alert, Critical, Error, Warning, Notice, Info, Debug
               When you select a Level, all the levels that appear above it in the list
               also trigger a syslog entry. For example, if you select Error, all Error,
               Critical, Alert, and Emergency events will be logged."
      ::= { syslogInfo 4}

  
   syslogPrimaryTunnel OBJECT-TYPE
      SYNTAX      DisplayString(SIZE(0..14))
      MAX-ACCESS  read-write
      STATUS      current
      DESCRIPTION
              "The HTTP tunnel associated with the primary host."
      ::= { syslogInfo 5}
 
   syslogSecondaryTunnel OBJECT-TYPE
      SYNTAX      DisplayString(SIZE(0..14))
      MAX-ACCESS  read-write
      STATUS      current
      DESCRIPTION
              "The HTTP tunnel associated with the secondary host."
      ::= { syslogInfo 6}

-- Email Info

   emailStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { emailInfo 1}

   emailActive OBJECT-TYPE
      SYNTAX      OnOffValue
      MAX-ACCESS  read-write
      STATUS      current
      DESCRIPTION
              "Determines whether or not email notification
               is turned on. Default is Off."
      ::= { emailInfo 2}

   emailLevel OBJECT-TYPE
      SYNTAX      INTEGER {
        emergency(1),
        alert(2),
        critical(3),
        error(4),
        warning(5),
        notice(6),
        informational(7),
        debug(8)
      }
      MAX-ACCESS  read-write
      STATUS      current
      DESCRIPTION
              "Choose the event level that triggers an email notification:
               Emergency, Alert, Critical, Error, Warning, Notice, Info, or
               Debug. You are selecting the lowest notification level;
               therefore, when you select Debug, you will get an email
               notification for all events that trigger a message."
      ::= { emailInfo 3}

   emailTo OBJECT-TYPE
      SYNTAX      DisplayString(SIZE(0..64))
      MAX-ACCESS  read-write
      STATUS      current
      DESCRIPTION
              "An email address or list of email addresses that will
               receive the email notification."
      ::= { emailInfo 4}

   emailFrom OBJECT-TYPE
      SYNTAX      DisplayString(SIZE(0..32))
      MAX-ACCESS  read-write
      STATUS      current
      DESCRIPTION
              "This field can contain an email address that might
               identify the Device Server name or some other value."
      ::= { emailInfo 5}

   emailSMTPHost OBJECT-TYPE
      SYNTAX      DisplayString(SIZE(0..64))
      MAX-ACCESS  read-write
      STATUS      current
      DESCRIPTION
              "The SMTP host (email server) that will process the
               email notification request. This can be either a host
               name defined in the Device Server host table or the
               SMTP host IP address."
      ::= { emailInfo 6}

   emailReply OBJECT-TYPE
      SYNTAX      DisplayString(SIZE(0..32))
      MAX-ACCESS  read-write
      STATUS      current
      DESCRIPTION
              "The email address to whom all replies to the email
               notification should go."
      ::= { emailInfo 7}

   emailSubject OBJECT-TYPE
      SYNTAX      DisplayString(SIZE(0..48))
      MAX-ACCESS  read-write
      STATUS      current
      DESCRIPTION
              "A text string, which can contain spaces, that will
               display in the Subject field of the email notification."
      ::= { emailInfo 8}

   emailSMTPUsername OBJECT-TYPE
      SYNTAX      DisplayString(SIZE(0..64))
      MAX-ACCESS  read-write
      STATUS      current
      DESCRIPTION
              "The username for the SMTP server, if the server requires
               authentication."
      ::= { emailInfo 9}
      
   emailSMTPPassword OBJECT-TYPE
      SYNTAX      DisplayString(SIZE(0..64))
      MAX-ACCESS  read-write
      STATUS      current
      DESCRIPTION
              "The password for the SMTP server, if the server requires
               authentication."
      ::= { emailInfo 10}
      
   emailSMTPEncryption OBJECT-TYPE
      SYNTAX      INTEGER {
        none(1),
        tls(2),
        ssl(3)
      }
      MAX-ACCESS  read-write
      STATUS      current
      DESCRIPTION
              "The encryption method for the SMTP server."
      ::= { emailInfo 11}
      
   emailSMTPValidatePeerCertificate OBJECT-TYPE
      SYNTAX      OnOffValue
      MAX-ACCESS  read-write
      STATUS      current
      DESCRIPTION
              "Validate peer SSL/TLS certificate, when SSL or TLS
               encryption is used."
      ::= { emailInfo 12}
      
  emailSMTPTcpPort OBJECT-TYPE
      SYNTAX      Integer32(1..65535)
      MAX-ACCESS  read-write
      STATUS      current
      DESCRIPTION
              "The TCP port used for communicating with the SMTP server.
               For no encryption or TLS encryption, use port 25.  
               For SSL encryption, use port 465."
      ::= { emailInfo 13 }
      
   emailSMTPDomain OBJECT-TYPE
      SYNTAX      DisplayString(SIZE(0..32))
      MAX-ACCESS  read-write
      STATUS      current
      DESCRIPTION
              "The domain for NTLM authentication with the SMTP server, if
               applicable."
      ::= { emailInfo 14 }
      
  emailSMTPHostTunnel OBJECT-TYPE
      SYNTAX      DisplayString(SIZE(0..14))
      MAX-ACCESS  read-write
      STATUS      current
      DESCRIPTION
              "The HTTP tunnel associated with the SMTP host."
      ::= { emailInfo 15 }
  

-- RIP Info

  ripStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ripInfo 1}

   ripMode OBJECT-TYPE
      SYNTAX      INTEGER {
        none(1),
        send(2),
        listen(3),
        sendandlisten(4)
      }
      MAX-ACCESS  read-write
      STATUS      current
      DESCRIPTION
              "Enable/disable RIP (Routing Information Protocol) mode
               for the Ethernet interface with one of the following options:
               None-Disables RIP over the Ethernet interface.
               Send-Sends RIP over the Ethernet interface.
               Listen-Listens for RIP over the Ethernet interface.
               Send and Listen-Sends RIP and listens for RIP over the
               Ethernet interface."
      ::= { ripInfo 2}

   ripAuthentication OBJECT-TYPE
      SYNTAX      INTEGER {
        none(1),
        password(2),
        md5(3)
      }
      MAX-ACCESS  read-write
      STATUS      current
      DESCRIPTION
              "Specify the type of RIP authentication:
               None-No authentication for RIP.
               Password-Simple RIP password authentication.
               MD5-Use MD5 RIP authentication."
      ::= { ripInfo 3}


  --  A table of RIP key entries, each entry indexed by chain number
  --  and entry number.

  ripKeysInfoTable OBJECT-TYPE
      SYNTAX      SEQUENCE OF RipKeysInfoEntry
      MAX-ACCESS  not-accessible
      STATUS      current
      DESCRIPTION
              "The RIP authentication keys info table."
      ::= { ripInfo 4 }

  ripKeysInfoEntry OBJECT-TYPE
      SYNTAX      RipKeysInfoEntry
      MAX-ACCESS  not-accessible
      STATUS      current
      DESCRIPTION
              "An entry in the ripKeysInfoTable, each relating to a
               RIP authentication key."
      INDEX   { ripKeysChainIndex, ripKeysKeyIndex }
      ::= { ripKeysInfoTable 1 }

  RipKeysInfoEntry ::=
      SEQUENCE {
        ripKeysChainIndex              GenericTableIndex,
        ripKeysKeyIndex              GenericTableIndex,
        ripKeyStatus            ContainerStatus,
        ripKeyId              Integer32,
        ripKeyStartDate              Date,
        ripKeyStartTime              Time,
        ripKeyEndDate              Date,
        ripKeyEndTime              Time
      }

  ripKeysChainIndex OBJECT-TYPE
      SYNTAX      GenericTableIndex
      MAX-ACCESS  not-accessible
      STATUS      current
      DESCRIPTION
              "The key chain index for this RIP authentication key."
      ::= { ripKeysInfoEntry 1 }

  ripKeysKeyIndex OBJECT-TYPE
      SYNTAX      GenericTableIndex
      MAX-ACCESS  not-accessible
      STATUS      current
      DESCRIPTION
              "The key index in the chain for this RIP authentication key."
      ::= { ripKeysInfoEntry 2 }

  ripKeyStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ripKeysInfoEntry 3 }

  ripKeyId OBJECT-TYPE
      SYNTAX      Integer32(0..255)
      MAX-ACCESS  read-write
      STATUS      current
      DESCRIPTION
              "The key Id for this RIP authentication key."
      ::= { ripKeysInfoEntry 4 }

  ripKeyStartDate OBJECT-TYPE
      SYNTAX      Date
      MAX-ACCESS  read-write
      STATUS      current
      DESCRIPTION
              "The starting date for which this
               RIP authentication key becomes effective.
               Format dd/mm/yyyy"
      ::= { ripKeysInfoEntry 5 }

  ripKeyStartTime OBJECT-TYPE
      SYNTAX      Time
      MAX-ACCESS  read-write
      STATUS      current
      DESCRIPTION
              "The starting time (local time) for which this
               RIP authentication key becomes effective.
               Format hh:mm:ss"
      ::= { ripKeysInfoEntry 6 }

  ripKeyEndDate OBJECT-TYPE
      SYNTAX      Date
      MAX-ACCESS  read-write
      STATUS      current
      DESCRIPTION
              "The end date , after which this
               RIP authentication key is no longer in effect."
      ::= { ripKeysInfoEntry 7 }

  ripKeyEndTime OBJECT-TYPE
      SYNTAX      Time
      MAX-ACCESS  read-write
      STATUS      current
      DESCRIPTION
              "The end time (local time), after which this
               RIP authentication key is no longer in effect."
      ::= { ripKeysInfoEntry 8 }

  --  timeInfo group.

  timeStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { timeInfo 1 }

  timeZoneName OBJECT-TYPE
      SYNTAX      DisplayString(SIZE(0..4))
      MAX-ACCESS  read-write
      STATUS      current
      DESCRIPTION
              "The name of the time zone when using standard time."
      ::= { timeInfo 2 }

  timeOffset OBJECT-TYPE
      SYNTAX      Integer32(-720..840)
      MAX-ACCESS  read-write
      STATUS      current
      DESCRIPTION
              "The offset of summer time from standard time in minutes."
      ::= { timeInfo 3 }

  timeSummerName OBJECT-TYPE
      SYNTAX      DisplayString(SIZE(0..4))
      MAX-ACCESS  read-write
      STATUS      current
      DESCRIPTION
              "The name of the time zone when using summer time."
      ::= { timeInfo 4 }

  timeSummerOffset OBJECT-TYPE
      SYNTAX      Integer32(0..180)
      MAX-ACCESS  read-write
      STATUS      current
      DESCRIPTION
              "The offset of summer time from standard time in minutes."
      ::= { timeInfo 5 }

  timeSummerMode OBJECT-TYPE
      SYNTAX      INTEGER {
        disabled(1),
        fixed(2),
        recurring(3)
      }
      MAX-ACCESS  read-write
      STATUS      current
      DESCRIPTION
              "You can configure the summer time to take effect:
               None-No summer time change.
               Fixed-The summer time change goes into effect at
                  the specified time every year. For example,
                  April 15 at 1:00 pm.
               Recurring-The summer time changes goes into effect
                  every year at same relative time. For example,
                  on the third week in April on a Tuesday at 1:00 pm."
      ::= { timeInfo 6 }

  timeSummerRecStartMonth OBJECT-TYPE
      SYNTAX      INTEGER {
        january(1),
        february(2),
        march(3),
        april(4),
        may(5),
        june(6),
        july(7),
        august(8),
        september(9),
        october(10),
        november(11),
        december(12)
      }
      MAX-ACCESS  read-write
      STATUS      current
      DESCRIPTION
              "The recurring summer time start month."
      ::= { timeInfo 7 }

  timeSummerRecStartWeek OBJECT-TYPE
      SYNTAX      INTEGER {
        first(1),
        second(2),
        third(3),
        fourth(4),
        last(5)
      }
      MAX-ACCESS  read-write
      STATUS      current
      DESCRIPTION
              "The recurring summer time start week."
      ::= { timeInfo 8}

  timeSummerRecStartDay OBJECT-TYPE
      SYNTAX      INTEGER {
        sunday(1),
        monday(2),
        tuesday(3),
        wednesday(4),
        thursday(5),
        friday(6),
        saturday(7)
      }
      MAX-ACCESS  read-write
      STATUS      current
      DESCRIPTION
              "The recurring summer time start day."
      ::= { timeInfo 9}

  timeSummerRecStartHour OBJECT-TYPE
      SYNTAX      Integer32(0..23)
      MAX-ACCESS  read-write
      STATUS      current
      DESCRIPTION
              "The recurring summer time start hour."
      ::= { timeInfo 10}

  timeSummerRecStartMin OBJECT-TYPE
      SYNTAX      Integer32(0..59)
      MAX-ACCESS  read-write
      STATUS      current
      DESCRIPTION
              "The recurring summer time start minute"
      ::= { timeInfo 11}

  timeSummerRecEndMonth OBJECT-TYPE
      SYNTAX      INTEGER {
        january(1),
        february(2),
        march(3),
        april(4),
        may(5),
        june(6),
        july(7),
        august(8),
        september(9),
        october(10),
        november(11),
        december(12)
      }
      MAX-ACCESS  read-write
      STATUS      current
      DESCRIPTION
              "The recurring summer time end month."
      ::= { timeInfo 12 }

  timeSummerRecEndWeek OBJECT-TYPE
      SYNTAX      INTEGER {
        first(1),
        second(2),
        third(3),
        fourth(4),
        last(5)
      }
      MAX-ACCESS  read-write
      STATUS      current
      DESCRIPTION
              "The recurring summer time end week."
      ::= { timeInfo 13 }

  timeSummerRecEndDay OBJECT-TYPE
      SYNTAX      INTEGER {
        sunday(1),
        monday(2),
        tuesday(3),
        wednesday(4),
        thursday(5),
        friday(6),
        saturday(7)
      }
      MAX-ACCESS  read-write
      STATUS      current
      DESCRIPTION
              "The recurring summer time end day."
      ::= { timeInfo 14 }

  timeSummerRecEndHour OBJECT-TYPE
      SYNTAX      Integer32(0..23)
      MAX-ACCESS  read-write
      STATUS      current
      DESCRIPTION
              "The recurring summer time end hour"
      ::= { timeInfo 15 }

  timeSummerRecEndMin OBJECT-TYPE
      SYNTAX      Integer32(0..59)
      MAX-ACCESS  read-write
      STATUS      current
      DESCRIPTION
              "The recurring summer time end minute"
      ::= { timeInfo 16 }

  timeSummerFixStartMonth OBJECT-TYPE
      SYNTAX      INTEGER {
        january(1),
        february(2),
        march(3),
        april(4),
        may(5),
        june(6),
        july(7),
        august(8),
        september(9),
        october(10),
        november(11),
        december(12)
      }
      MAX-ACCESS  read-write
      STATUS      current
      DESCRIPTION
              "The fixed summer time start month"
      ::= { timeInfo 17 }

  timeSummerFixStartDay OBJECT-TYPE
      SYNTAX      Integer32(1..31)
      MAX-ACCESS  read-write
      STATUS      current
      DESCRIPTION
              "The fixed summer time start day"
      ::= { timeInfo 18 }

  timeSummerFixStartHour OBJECT-TYPE
      SYNTAX      Integer32(0..23)
      MAX-ACCESS  read-write
      STATUS      current
      DESCRIPTION
              "The fixed summer time start hour"
      ::= { timeInfo 19 }

  timeSummerFixStartMinute OBJECT-TYPE
      SYNTAX      Integer32(0..59)
      MAX-ACCESS  read-write
      STATUS      current
      DESCRIPTION
              "The fixed summer time start minute"
      ::= { timeInfo 20 }

  timeSummerFixEndMonth OBJECT-TYPE
      SYNTAX      INTEGER {
        january(1),
        february(2),
        march(3),
        april(4),
        may(5),
        june(6),
        july(7),
        august(8),
        september(9),
        october(10),
        november(11),
        december(12)
      }
      MAX-ACCESS  read-write
      STATUS      current
      DESCRIPTION
              "The fixed summer time End month"
      ::= { timeInfo 21 }

  timeSummerFixEndDay OBJECT-TYPE
      SYNTAX      Integer32(1..31)
      MAX-ACCESS  read-write
      STATUS      current
      DESCRIPTION
              "The fixed summer time End day"
      ::= { timeInfo 22 }

  timeSummerFixEndHour OBJECT-TYPE
      SYNTAX      Integer32(0..23)
      MAX-ACCESS  read-write
      STATUS      current
      DESCRIPTION
              "The fixed summer time End hour"
      ::= { timeInfo 23 }

  timeSummerFixEndMinute OBJECT-TYPE
      SYNTAX      Integer32(0..59)
      MAX-ACCESS  read-write
      STATUS      current
      DESCRIPTION
              "The fixed summer time End minute"
      ::= { timeInfo 24 }

  timeSntpMode OBJECT-TYPE
      SYNTAX      INTEGER {
        disabled(1),
        unicast(2),
        multicast(3),
        anycast(4)
      }
      MAX-ACCESS  read-write
      STATUS      current
      DESCRIPTION
              "The sntp client mode.  Valid modes are Unicast, Multicast or Anycast"
      ::= { timeInfo 25 }

  timeSntpVersion OBJECT-TYPE
      SYNTAX      INTEGER  {
        version1(1),
        version2(2),
        version3(3),
        version4(4)
      }
      MAX-ACCESS  read-write
      STATUS      current
      DESCRIPTION
              "The sntp client version."
      ::= { timeInfo 26 }

  timeSntpHost1 OBJECT-TYPE
      SYNTAX      DisplayString(SIZE(0..14))
      MAX-ACCESS  read-write
      STATUS      current
      DESCRIPTION
              "The first remote SNTP host name that the device server communicates with."
      ::= { timeInfo 27 }

  timeSntpHost2 OBJECT-TYPE
      SYNTAX      DisplayString(SIZE(0..14))
      MAX-ACCESS  read-write
      STATUS      current
      DESCRIPTION
              "The second remote SNTP host name that the device server communicates with."
      ::= { timeInfo 28 }

  
  timeSntpTunnelName1 OBJECT-TYPE
      SYNTAX      DisplayString(SIZE(0..14))
      MAX-ACCESS  read-write
      STATUS      current
      DESCRIPTION
              "The HTTP tunnel associated with the first host."
      ::= { timeInfo 29 }

  timeSntpTunnelName2 OBJECT-TYPE
      SYNTAX      DisplayString(SIZE(0..14))
      MAX-ACCESS  read-write
      STATUS      current
      DESCRIPTION
              "The HTTP tunnel associated with the second host."
      ::= { timeInfo 30 }

  serverSntpServerAuthentication OBJECT-TYPE
      SYNTAX      INTEGER {
               off(1),
               on(2)
      }
      MAX-ACCESS  read-write
      STATUS      current
      DESCRIPTION
              "Specifies whether the iolan with authenticate the ntp time 
               server."
      ::= { timeInfo 31 }

  serverSntpKeyID OBJECT-TYPE
      SYNTAX      INTEGER
      MAX-ACCESS  read-write
      STATUS      current
      DESCRIPTION
              "Specifies the key ID to use for host 1 during server authentication."
      ::= { timeInfo 32 }
  
  serverSntpKeyID2 OBJECT-TYPE
      SYNTAX      INTEGER
      MAX-ACCESS  read-write
      STATUS      current
      DESCRIPTION
              "Specifies the key ID to use for host 2 during server authentication."
      ::= { timeInfo 33 }
  
  --****************************************************************************
  --  fileInfo group.

  fileStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { fileInfo 1}

  fileFirmwareHost OBJECT-TYPE
      SYNTAX      DisplayString(SIZE(0..46))
      MAX-ACCESS  read-write
      STATUS      current
      DESCRIPTION
              "The host name or IP address of the server that contains the firmware file.
               If you use a host name, it must exist in the Device Server's host table
               or be resolved by DNS."
      ::= { fileInfo 2}

  fileFirmwareName OBJECT-TYPE
      SYNTAX      DisplayString(SIZE(0..64))
      MAX-ACCESS  read-write
      STATUS      current
      DESCRIPTION
              "The path and file name (do not use a drive letter), relative to the default
               path of your TFTP server software, of the update software for the Device
               Server that will be loaded when the Device Server is rebooted."
      ::= { fileInfo 3}

  fileConfigurationHost OBJECT-TYPE
      SYNTAX      DisplayString(SIZE(0..46))
      MAX-ACCESS  read-write
      STATUS      current
      DESCRIPTION
              "The host name or IP address of the server that contains the configuration file.
               If you use a host name, it must exist in the Device Server's host table
               or be resolved by DNS."
      ::= { fileInfo 4}

  fileConfigurationName OBJECT-TYPE
      SYNTAX      DisplayString(SIZE(0..64))
      MAX-ACCESS  read-write
      STATUS      current
      DESCRIPTION
              "The path and file name (do not use a drive letter), relative to the default
               path of your TFTP server software, of the new configuration file for the Device
               Server that will be loaded when the Device Server is rebooted."
      ::= { fileInfo 5}

  fileMOTDHost OBJECT-TYPE
      SYNTAX      DisplayString(SIZE(0..46))
      MAX-ACCESS  read-write
      STATUS      current
      DESCRIPTION
              "The host name or IP address of the server that contains the MOTD file.
               If you use a host name, it must exist in the Device Server's host table
               or be resolved by DNS."
      ::= { fileInfo 6}

  fileMOTDName OBJECT-TYPE
      SYNTAX      DisplayString(SIZE(0..64))
      MAX-ACCESS  read-write
      STATUS      current
      DESCRIPTION
              "The path and file name (do not use a drive letter), relative to the default
               path of your TFTP server software, of the file that contains a string that
               is displayed when a user connects to the Device Server."
      ::= { fileInfo 7}
  
  fileMOTDTunnel OBJECT-TYPE
      SYNTAX      DisplayString(SIZE(0..14))
      MAX-ACCESS  read-write
      STATUS      current
      DESCRIPTION
              "The HTTP tunnel associated with the MOTD host."
      ::= { fileInfo 8}
  

-- Ethernet Stats Info
  ethStatsInfoTable OBJECT-TYPE         
      SYNTAX      SEQUENCE OF EthStatsInfoEntry
      MAX-ACCESS  not-accessible
      STATUS      current
      DESCRIPTION
              "The Ethernet statistics table."
      ::= { ethStatsInfo 1 }

  ethStatsInfoEntry OBJECT-TYPE
      SYNTAX      EthStatsInfoEntry
      MAX-ACCESS  not-accessible
      STATUS      current
      DESCRIPTION
              "An entry in the Ethernet statistics table, each relating to an Ethernet interface."
      INDEX   { ethStatsIndex }
      ::= { ethStatsInfoTable 1 }

  EthStatsInfoEntry ::=
      SEQUENCE {
        ethStatsIndex               GenericTableIndex,
        ethStatsName                DisplayString,
        ethStatsMacAddress          MacAddress,
        ethStatsStatus              INTEGER,
        ethStatsBroadcast           YesNoValue,
        ethStatsDebug               YesNoValue,
        ethStatsLoopback            YesNoValue,
        ethStatsPointtoPoint        YesNoValue,
        ethStatsNoTrailers          YesNoValue,
        ethStatsRunning             YesNoValue,
        ethStatsNoArp               YesNoValue,
        ethStatsPromiscuous         YesNoValue,
        ethStatsRxMulticast         YesNoValue,
        ethStatsMasterLoadBalancer  YesNoValue,
        ethStatsSlaveLoadBalancer   YesNoValue,
        ethStatsMulticast           YesNoValue,
        ethStatsSetMedia            YesNoValue,
        ethStatsAutoMedia           YesNoValue,
        ethStatsDynamic             YesNoValue,
        ethStatsLocalAddress        IpAddress,
        ethStatsSubnetMask          IpAddress,
        ethStatsBroadcastAddress    IpAddress,
        ethStatsMtu                 Unsigned32,
        ethStatsTxQLen              Unsigned32,
        ethStatsRxBytes             Counter32,
        ethStatsTxBytes             Counter32,
        ethStatsRxPackets           Counter32,
        ethStatsTxPackets           Counter32,
        ethStatsRxErrors            Counter32,
        ethStatsTxPktErrors         Counter32,
        ethStatsRxDroppedPkts       Counter32,
        ethStatsTxDroppedPkts       Counter32,
        ethStatsRxOverruns          Counter32,
        ethStatsTxOverruns          Counter32,
        ethStatsRxFrameErrs         Counter32,
        ethStatsTxCarrierErrs       Counter32,
        ethStatsCollisions          Counter32
      }
  ethStatsIndex OBJECT-TYPE
      SYNTAX      GenericTableIndex
      MAX-ACCESS not-accessible
      STATUS      current
      DESCRIPTION
              "The Ethernet interface number."
      ::= { ethStatsInfoEntry 1 }

  ethStatsName OBJECT-TYPE
      SYNTAX      DisplayString
      MAX-ACCESS  read-only
      STATUS      current
      DESCRIPTION
              "Displays Ethernet statistics."
      ::= { ethStatsInfoEntry 2}

  ethStatsMacAddress OBJECT-TYPE
      SYNTAX      MacAddress
      MAX-ACCESS  read-only
      STATUS      current
      DESCRIPTION
              "Displays the MAC address."
      ::= { ethStatsInfoEntry 3}

  ethStatsStatus OBJECT-TYPE
      SYNTAX      INTEGER {
        down(1),
        up(2)
      }
      MAX-ACCESS  read-only
      STATUS      current
      DESCRIPTION
              "Displays the Ethernet status:
        1 is down and 2 is up."
      ::= { ethStatsInfoEntry 4}

  ethStatsBroadcast OBJECT-TYPE
      SYNTAX      YesNoValue
      MAX-ACCESS  read-only
      STATUS      current
      DESCRIPTION
              "ethStatsBroadcast"
      ::= { ethStatsInfoEntry 5}

  ethStatsDebug OBJECT-TYPE
      SYNTAX      YesNoValue
      MAX-ACCESS  read-only
      STATUS      current
      DESCRIPTION
              "ethStatsDebug"
      ::= { ethStatsInfoEntry 6}

  ethStatsLoopback OBJECT-TYPE
      SYNTAX      YesNoValue
      MAX-ACCESS  read-only
      STATUS      current
      DESCRIPTION
              "ethStatsLoopback"
      ::= { ethStatsInfoEntry 7}

  ethStatsPointtoPoint OBJECT-TYPE
      SYNTAX      YesNoValue
      MAX-ACCESS  read-only
      STATUS      current
      DESCRIPTION
              "ethStatsPointtoPoint"
      ::= { ethStatsInfoEntry 8}

  ethStatsNoTrailers OBJECT-TYPE
      SYNTAX      YesNoValue
      MAX-ACCESS  read-only
      STATUS      current
      DESCRIPTION
              "ethStatsNoTrailers"
      ::= { ethStatsInfoEntry 9}

  ethStatsRunning OBJECT-TYPE
      SYNTAX      YesNoValue
      MAX-ACCESS  read-only
      STATUS      current
      DESCRIPTION
              "ethStatsRunning"
      ::= { ethStatsInfoEntry 10}

  ethStatsNoArp OBJECT-TYPE
      SYNTAX      YesNoValue
      MAX-ACCESS  read-only
      STATUS      current
      DESCRIPTION
              "ethStatsNoArp"
      ::= { ethStatsInfoEntry 11}

  ethStatsPromiscuous OBJECT-TYPE
      SYNTAX      YesNoValue
      MAX-ACCESS  read-only
      STATUS      current
      DESCRIPTION
              "ethStatsPromiscuous"
      ::= { ethStatsInfoEntry 12}

  ethStatsRxMulticast OBJECT-TYPE
      SYNTAX      YesNoValue
      MAX-ACCESS  read-only
      STATUS      current
      DESCRIPTION
              "ethStatsRxMulticast"
      ::= { ethStatsInfoEntry 13}

  ethStatsMasterLoadBalancer OBJECT-TYPE
      SYNTAX      YesNoValue
      MAX-ACCESS  read-only
      STATUS      current
      DESCRIPTION
              "ethStatsMasterLoadBalancer"
      ::= { ethStatsInfoEntry 14}

  ethStatsSlaveLoadBalancer OBJECT-TYPE
      SYNTAX      YesNoValue
      MAX-ACCESS  read-only
      STATUS      current
      DESCRIPTION
              "ethStatsSlaveLoadBalancer"
      ::= { ethStatsInfoEntry 15}

  ethStatsMulticast OBJECT-TYPE
      SYNTAX      YesNoValue
      MAX-ACCESS  read-only
      STATUS      current
      DESCRIPTION
              "ethStatsMulticast"
      ::= { ethStatsInfoEntry 16}

  ethStatsSetMedia OBJECT-TYPE
      SYNTAX      YesNoValue
      MAX-ACCESS  read-only
      STATUS      current
      DESCRIPTION
              "ethStatsSetMedia"
      ::= { ethStatsInfoEntry 17}

  ethStatsAutoMedia OBJECT-TYPE
      SYNTAX      YesNoValue
      MAX-ACCESS  read-only
      STATUS      current
      DESCRIPTION
              "ethStatsAutoMedia"
      ::= { ethStatsInfoEntry 18}

  ethStatsDynamic OBJECT-TYPE
      SYNTAX      YesNoValue
      MAX-ACCESS  read-only
      STATUS      current
      DESCRIPTION
              "ethStatsDynamic"
      ::= { ethStatsInfoEntry 19}

  ethStatsLocalAddress OBJECT-TYPE
      SYNTAX      IpAddress
      MAX-ACCESS  read-only
      STATUS      current
      DESCRIPTION
              "ethStatsLocalAddress"
      ::= { ethStatsInfoEntry 20}

  ethStatsSubnetMask OBJECT-TYPE
      SYNTAX      IpAddress
      MAX-ACCESS  read-only
      STATUS      current
      DESCRIPTION
              "ethStatsSubnetMask"
      ::= { ethStatsInfoEntry 21}

  ethStatsBroadcastAddress OBJECT-TYPE
      SYNTAX      IpAddress
      MAX-ACCESS  read-only
      STATUS      current
      DESCRIPTION
              "ethStatsBroadcastAddress"
      ::= { ethStatsInfoEntry 22}

  ethStatsMtu OBJECT-TYPE
      SYNTAX      Unsigned32
      MAX-ACCESS  read-only
      STATUS      current
      DESCRIPTION
              "ethStatsMtu"
      ::= { ethStatsInfoEntry 23}

  ethStatsTxQLen OBJECT-TYPE
      SYNTAX      Unsigned32
      MAX-ACCESS  read-only
      STATUS      current
      DESCRIPTION
              "ethStatsTxQLen"
      ::= { ethStatsInfoEntry 24}

  ethStatsRxBytes OBJECT-TYPE
      SYNTAX      Counter32
      MAX-ACCESS  read-only
      STATUS      current
      DESCRIPTION
              "ethStatsRxBytes"
      ::= { ethStatsInfoEntry 25}

  ethStatsTxBytes OBJECT-TYPE
      SYNTAX      Counter32
      MAX-ACCESS  read-only
      STATUS      current
      DESCRIPTION
              "ethStatsTxBytes"
      ::= { ethStatsInfoEntry 26}

  ethStatsRxPackets OBJECT-TYPE
      SYNTAX      Counter32
      MAX-ACCESS  read-only
      STATUS      current
      DESCRIPTION
              "ethStatsRxPackets"
      ::= { ethStatsInfoEntry 27}

  ethStatsTxPackets OBJECT-TYPE
      SYNTAX      Counter32
      MAX-ACCESS  read-only
      STATUS      current
      DESCRIPTION
              "ethStatsTxPackets"
      ::= { ethStatsInfoEntry 28}

  ethStatsRxErrors OBJECT-TYPE
      SYNTAX      Counter32
      MAX-ACCESS  read-only
      STATUS      current
      DESCRIPTION
              "ethStatsRxErrors"
      ::= { ethStatsInfoEntry 29}

  ethStatsTxPktErrors OBJECT-TYPE
      SYNTAX      Counter32
      MAX-ACCESS  read-only
      STATUS      current
      DESCRIPTION
              "ethStatsTxPktErrors"
      ::= { ethStatsInfoEntry 30}

  ethStatsRxDroppedPkts OBJECT-TYPE
      SYNTAX      Counter32
      MAX-ACCESS  read-only
      STATUS      current
      DESCRIPTION
              "ethStatsRxDroppedPkts"
      ::= { ethStatsInfoEntry 31}

  ethStatsTxDroppedPkts OBJECT-TYPE
      SYNTAX      Counter32
      MAX-ACCESS  read-only
      STATUS      current
      DESCRIPTION
              "ethStatsTxDroppedPkts"
      ::= { ethStatsInfoEntry 32}

  ethStatsRxOverruns OBJECT-TYPE
      SYNTAX      Counter32
      MAX-ACCESS  read-only
      STATUS      current
      DESCRIPTION
              "ethStatsRxOverruns"
      ::= { ethStatsInfoEntry 33}

  ethStatsTxOverruns OBJECT-TYPE
      SYNTAX      Counter32
      MAX-ACCESS  read-only
      STATUS      current
      DESCRIPTION
              "ethStatsTxOverruns"
      ::= { ethStatsInfoEntry 34}

  ethStatsRxFrameErrs OBJECT-TYPE
      SYNTAX      Counter32
      MAX-ACCESS  read-only
      STATUS      current
      DESCRIPTION
              "ethStatsRxFrameErrs"
      ::= { ethStatsInfoEntry 35}

  ethStatsTxCarrierErrs OBJECT-TYPE
      SYNTAX      Counter32
      MAX-ACCESS  read-only
      STATUS      current
      DESCRIPTION
              "ethStatsTxCarrierErrs"
      ::= { ethStatsInfoEntry 36}

  ethStatsCollisions OBJECT-TYPE
      SYNTAX      Counter32
      MAX-ACCESS  read-only
      STATUS      current
      DESCRIPTION
              "ethStatsCollisions"
      ::= { ethStatsInfoEntry 37}

-- SNTP Stats Info

  sntpStatsAddress OBJECT-TYPE
      SYNTAX      DisplayString
      MAX-ACCESS  read-only
      STATUS      current
      DESCRIPTION
              "sntpStatsAddress"
      ::= { sntpStatsInfo 1}

  sntpStatsLastUpdate OBJECT-TYPE
      SYNTAX      DisplayString
      MAX-ACCESS  read-only
      STATUS      current
      DESCRIPTION
              "sntpStatsLastUpdate"
      ::= { sntpStatsInfo 2}

  sntpStatsLeapIndicator OBJECT-TYPE
      SYNTAX      INTEGER {
         noWarning(1),
         minutes61(2),
         minutes59(3),
         alarm(4)
      }
      MAX-ACCESS  read-only
      STATUS      current
      DESCRIPTION
              "sntpStatsLeapIndicator"
      ::= { sntpStatsInfo 3}

  sntpStatsVersion OBJECT-TYPE
      SYNTAX      INTEGER {
        ipV4(3),
        ipv4ipv6osi(4)
      }
      MAX-ACCESS  read-only
      STATUS      current
      DESCRIPTION
              "sntpStatsVersion"
      ::= { sntpStatsInfo 4}

  sntpStatsMode OBJECT-TYPE
      SYNTAX      INTEGER {
         reserved(1),
         symmetricActive(2),
         symmetricPassive(3),
         client(4),
         server(5),
         broadcast(6),
         reservedNTP(7),
         reserved2(8)
      }
      MAX-ACCESS  read-only
      STATUS      current
      DESCRIPTION
              "sntpStatsMode"
      ::= { sntpStatsInfo 5}

  sntpStatsStratum OBJECT-TYPE
      SYNTAX      Integer32(0..15)
      MAX-ACCESS  read-only
      STATUS      current
      DESCRIPTION
              "sntpStatsStratum"
      ::= { sntpStatsInfo 6}

  sntpStatsRefId OBJECT-TYPE
      SYNTAX      Unsigned32
      MAX-ACCESS  read-only
      STATUS      current
      DESCRIPTION
              "sntpStatsRefId"
      ::= { sntpStatsInfo 7}

  sntpStatsOffset OBJECT-TYPE
      SYNTAX      Unsigned32
      MAX-ACCESS  read-only
      STATUS      current
      DESCRIPTION
              "sntpStats"
      ::= { sntpStatsInfo 8}

-- Rip (V4) Info
  ripInfoTable OBJECT-TYPE
      SYNTAX      SEQUENCE OF RipInfoEntry
      MAX-ACCESS  not-accessible
      STATUS      current
      DESCRIPTION
              "The rip info table."
      ::= { ripTableInfo 1 }

  ripInfoEntry OBJECT-TYPE
      SYNTAX      RipInfoEntry
      MAX-ACCESS  not-accessible
      STATUS      current
      DESCRIPTION
              "An entry in the ripInfoTable, each relating to a rip entry."
      INDEX   { ripIndex }
      ::= { ripInfoTable 1 }

  RipInfoEntry ::=
      SEQUENCE {
        ripIndex              GenericTableIndex,
        ripTableIpAddr        IpAddress,
        ripTableLastUpdate    Unsigned32,
        ripTableVersion       Unsigned32,
        ripTableAuthType      INTEGER,
        ripTableSequence      Unsigned32,
        ripTableBadPackets    Counter32,
        ripTableBadRoutes     Counter32
      }

  ripIndex OBJECT-TYPE
      SYNTAX      GenericTableIndex
      MAX-ACCESS  not-accessible
      STATUS      current
      DESCRIPTION
              "The table entry number for this rip."
      ::= { ripInfoEntry 1 }

  ripTableIpAddr OBJECT-TYPE
      SYNTAX      IpAddress
      MAX-ACCESS  read-only
      STATUS      current
      DESCRIPTION
              "ripIpAddr"
      ::= { ripInfoEntry 2 }

  ripTableLastUpdate OBJECT-TYPE
      SYNTAX      Unsigned32
      MAX-ACCESS  read-only
      STATUS      current
      DESCRIPTION
              "Last Update in Seconds"
      ::= { ripInfoEntry 3 }

  ripTableVersion OBJECT-TYPE
      SYNTAX      Unsigned32
      MAX-ACCESS  read-only
      STATUS      current
      DESCRIPTION
              "Version"
      ::= { ripInfoEntry 4 }

  ripTableAuthType OBJECT-TYPE
      SYNTAX      INTEGER {
        noAuth(1),
        authData(2),
        password(3),
        md5(4)
      }
      MAX-ACCESS  read-only
      STATUS      current
      DESCRIPTION
              "Authentication Type"
      ::= { ripInfoEntry 5 }

  ripTableSequence OBJECT-TYPE
      SYNTAX      Unsigned32
      MAX-ACCESS  read-only
      STATUS      current
      DESCRIPTION
              "Sequence"
      ::= { ripInfoEntry 6 }

  ripTableBadPackets OBJECT-TYPE
      SYNTAX      Counter32
      MAX-ACCESS  read-only
      STATUS      current
      DESCRIPTION
              "ripTableBadPackets"
      ::= { ripInfoEntry 7 }

  ripTableBadRoutes OBJECT-TYPE
      SYNTAX      Counter32
      MAX-ACCESS  read-only
      STATUS      current
      DESCRIPTION
              "ripTableBadRoutes"
      ::= { ripInfoEntry 8 }

-- TCP Conn Stats

  tcpConnTable OBJECT-TYPE
      SYNTAX      SEQUENCE OF TcpConnEntry
      MAX-ACCESS  not-accessible
      STATUS      current
      DESCRIPTION
              "tcpConnTable."
      ::= { tcpConnStatsInfo 1 }

  tcpConnEntry OBJECT-TYPE
      SYNTAX      TcpConnEntry
      MAX-ACCESS  not-accessible
      STATUS      current
      DESCRIPTION
              "An entry in the tcpConnTable"
      INDEX   { tcpConnIndex }
      ::= { tcpConnTable 1 }

  TcpConnEntry ::=
      SEQUENCE {
        tcpConnIndex          GenericTableIndex,
        tcpConnLocalAddress   IpAddress,
        tcpConnLocalPort      Integer32,
        tcpConnRemoteAddress  IpAddress,
        tcpConnRemotePort     Integer32,
        tcpConnTxQueueBytes   Counter32,
        tcpConnRxQueueBytes   Counter32,
        tcpConnState          INTEGER
        }

  tcpConnIndex OBJECT-TYPE
      SYNTAX      GenericTableIndex
      MAX-ACCESS  not-accessible
      STATUS      current
      DESCRIPTION
              "Index"
      ::= { tcpConnEntry 1 }

  tcpConnLocalAddress OBJECT-TYPE
      SYNTAX      IpAddress
      MAX-ACCESS  read-only
      STATUS      current
      DESCRIPTION
              "LocalAddress"
      ::= { tcpConnEntry 2}

  tcpConnLocalPort OBJECT-TYPE
      SYNTAX      Integer32(0..65535)
      MAX-ACCESS  read-only
      STATUS      current
      DESCRIPTION
              "LocalPort"
      ::= { tcpConnEntry 3}

  tcpConnRemoteAddress OBJECT-TYPE
      SYNTAX      IpAddress
      MAX-ACCESS  read-only
      STATUS      current
      DESCRIPTION
              "RemoteAddress"
      ::= { tcpConnEntry 4}

  tcpConnRemotePort OBJECT-TYPE
      SYNTAX      Integer32(0..65535)
      MAX-ACCESS  read-only
      STATUS      current
      DESCRIPTION
              "RemotePort"
      ::= { tcpConnEntry 5}

  tcpConnTxQueueBytes OBJECT-TYPE
      SYNTAX      Counter32
      MAX-ACCESS  read-only
      STATUS      current
      DESCRIPTION
              "tcpConnTxQueueBytes"
      ::= { tcpConnEntry 6}

  tcpConnRxQueueBytes OBJECT-TYPE
      SYNTAX      Counter32
      MAX-ACCESS  read-only
      STATUS      current
      DESCRIPTION
              "tcpConnRxQueueBytes"
      ::= { tcpConnEntry 7}

  tcpConnState OBJECT-TYPE
      SYNTAX      INTEGER {
        established(1),
        synSent(2),
        synRecv(3),
        finWait1(4),
        finWait2(5),
        timewait(6),
        close(7),
        closeWait(8),
        lastack(9),
        listen(10),
        closing(11)
      }
      MAX-ACCESS  read-only
      STATUS      current
      DESCRIPTION
              "State"
      ::= { tcpConnEntry 8}

-- UDP Conn IPv6 Stats

  udpConnTable OBJECT-TYPE
      SYNTAX      SEQUENCE OF UdpConnEntry
      MAX-ACCESS  not-accessible
      STATUS      current
      DESCRIPTION
              "udpConnTable"
      ::= { udpConnStatsInfo 1 }

  udpConnEntry OBJECT-TYPE
      SYNTAX      UdpConnEntry
      MAX-ACCESS  not-accessible
      STATUS      current
      DESCRIPTION
              "An entry in the udpConnTable"
      INDEX   { udpConnIndex }
      ::= { udpConnTable 1 }

  UdpConnEntry ::=
      SEQUENCE {
        udpConnIndex              GenericTableIndex,
        udpConnLocalAddress       IpAddress,
        udpConnLocalPort          Integer32,
        udpConnRemoteAddress      IpAddress,
        udpConnRemotePort         Integer32,
        udpConnTxQueueBytes       Counter32,
        udpConnRxQueueBytes       Counter32,
        udpConnState             INTEGER
        }

  udpConnIndex OBJECT-TYPE
      SYNTAX      GenericTableIndex
      MAX-ACCESS  not-accessible
      STATUS      current
      DESCRIPTION
              "Index"
      ::= { udpConnEntry 1 }

  udpConnLocalAddress OBJECT-TYPE
      SYNTAX      IpAddress
      MAX-ACCESS  read-only
      STATUS      current
      DESCRIPTION
              "LocalAddress"
      ::= { udpConnEntry 2}

  udpConnLocalPort OBJECT-TYPE
      SYNTAX       Integer32(0..65535)
      MAX-ACCESS  read-only
      STATUS      current
      DESCRIPTION
              "LocalPort"
      ::= { udpConnEntry 3}

  udpConnRemoteAddress OBJECT-TYPE
      SYNTAX      IpAddress
      MAX-ACCESS  read-only
      STATUS      current
      DESCRIPTION
              "RemoteAddress"
      ::= { udpConnEntry 4}

  udpConnRemotePort OBJECT-TYPE
      SYNTAX      Integer32(0..65535)
      MAX-ACCESS  read-only
      STATUS      current
      DESCRIPTION
              "RemotePort"
      ::= { udpConnEntry 5}

  udpConnTxQueueBytes OBJECT-TYPE
      SYNTAX      Counter32
      MAX-ACCESS  read-only
      STATUS      current
      DESCRIPTION
              "udpConnTxQueueBytes"
      ::= { udpConnEntry 6}

  udpConnRxQueueBytes OBJECT-TYPE
      SYNTAX      Counter32
      MAX-ACCESS  read-only
      STATUS      current
      DESCRIPTION
              "udpConnRxQueueBytes"
      ::= { udpConnEntry 7}

  udpConnState OBJECT-TYPE
      SYNTAX      INTEGER {
          established(1)
      }
      MAX-ACCESS  read-only
      STATUS      current
      DESCRIPTION
              "State"
      ::= { udpConnEntry 8}

-- IPv6 Stats
   ipV6StatsRxTotalPkts OBJECT-TYPE
      SYNTAX       Counter32
      MAX-ACCESS   read-only
      STATUS       current
      DESCRIPTION
               "RxTotal"
      ::= {ipv6StatsInfo 1}

   ipV6StatsRxHdrErrors OBJECT-TYPE
      SYNTAX       Counter32
      MAX-ACCESS   read-only
      STATUS       current
      DESCRIPTION
               "RxHdrErrors"
      ::= {ipv6StatsInfo 2}

   ipV6StatsRxTooBigErrors OBJECT-TYPE
      SYNTAX       Counter32
      MAX-ACCESS   read-only
      STATUS       current
      DESCRIPTION
               "RxTooBigErrors"
      ::= {ipv6StatsInfo 3}

   ipV6StatsRxNoRoutes OBJECT-TYPE
      SYNTAX       Counter32
      MAX-ACCESS   read-only
      STATUS       current
      DESCRIPTION
               "RxNoRoutes"
      ::= {ipv6StatsInfo 4}

   ipV6StatsRxAddrErrors OBJECT-TYPE
      SYNTAX       Counter32
      MAX-ACCESS   read-only
      STATUS       current
      DESCRIPTION
               "RxAddrErrors"
      ::= {ipv6StatsInfo 5}

   ipV6StatsRxUnknownProtos OBJECT-TYPE
      SYNTAX       Counter32
      MAX-ACCESS   read-only
      STATUS       current
      DESCRIPTION
               "RxUnknownProtos"
      ::= {ipv6StatsInfo 6}

   ipV6StatsRxTruncatedPkts OBJECT-TYPE
      SYNTAX       Counter32
      MAX-ACCESS   read-only
      STATUS       current
      DESCRIPTION
               "RxTruncatedPkts"
      ::= {ipv6StatsInfo 7}

   ipV6StatsRxDiscards OBJECT-TYPE
      SYNTAX       Counter32
      MAX-ACCESS   read-only
      STATUS       current
      DESCRIPTION
               "RxDiscards"
      ::= {ipv6StatsInfo 8}

   ipV6StatsRxDelivers OBJECT-TYPE
      SYNTAX       Counter32
      MAX-ACCESS   read-only
      STATUS       current
      DESCRIPTION
               "RxDelivers"
      ::= {ipv6StatsInfo 9}

   ipV6StatsRxMcastPkts OBJECT-TYPE
      SYNTAX       Counter32
      MAX-ACCESS   read-only
      STATUS       current
      DESCRIPTION
               "RxMcastPkts"
      ::= {ipv6StatsInfo 10}

   ipV6StatsTxForwDatagrams OBJECT-TYPE
      SYNTAX       Counter32
      MAX-ACCESS   read-only
      STATUS       current
      DESCRIPTION
               "TxForwDatagrams"
      ::= {ipv6StatsInfo 11}

   ipV6StatsTxRequests OBJECT-TYPE
      SYNTAX       Counter32
      MAX-ACCESS   read-only
      STATUS       current
      DESCRIPTION
               "TxRequests"
      ::= {ipv6StatsInfo 12}

   ipV6StatsTxDiscards OBJECT-TYPE
      SYNTAX       Counter32
      MAX-ACCESS   read-only
      STATUS       current
      DESCRIPTION
               "TxDiscards"
      ::= {ipv6StatsInfo 13}

   ipV6StatsTxNoRoutes OBJECT-TYPE
      SYNTAX       Counter32
      MAX-ACCESS   read-only
      STATUS       current
      DESCRIPTION
               "TxNoRoutes"
      ::= {ipv6StatsInfo 14}

   ipV6StatsTxMcastPkts OBJECT-TYPE
      SYNTAX       Counter32
      MAX-ACCESS   read-only
      STATUS       current
      DESCRIPTION
               "TxMcastPkts"
      ::= {ipv6StatsInfo 15}

   ipV6StatsReasmTimeout OBJECT-TYPE
      SYNTAX       Unsigned32
      MAX-ACCESS   read-only
      STATUS       current
      DESCRIPTION
               "ReasmTimeout"
      ::= {ipv6StatsInfo 16}

   ipV6StatsReasmReqds OBJECT-TYPE
      SYNTAX       Counter32
      MAX-ACCESS   read-only
      STATUS       current
      DESCRIPTION
               "ReasmReqds"
      ::= {ipv6StatsInfo 17}

   ipV6StatsReasmOKs OBJECT-TYPE
      SYNTAX       Counter32
      MAX-ACCESS   read-only
      STATUS       current
      DESCRIPTION
               "ReasmOKs"
      ::= {ipv6StatsInfo 18}

   ipV6StatsReasmFails OBJECT-TYPE
      SYNTAX       Counter32
      MAX-ACCESS   read-only
      STATUS       current
      DESCRIPTION
               "ReasmFails"
      ::= {ipv6StatsInfo 19}

   ipV6StatsFragOKs OBJECT-TYPE
      SYNTAX       Counter32
      MAX-ACCESS   read-only
      STATUS       current
      DESCRIPTION
               "FragOKs"
      ::= {ipv6StatsInfo 20}

   ipV6StatsFragFails OBJECT-TYPE
      SYNTAX       Counter32
      MAX-ACCESS   read-only
      STATUS       current
      DESCRIPTION
               "FragFails"
      ::= {ipv6StatsInfo 21}

   ipV6StatsFragCreates OBJECT-TYPE
      SYNTAX       Counter32
      MAX-ACCESS   read-only
      STATUS       current
      DESCRIPTION
               "FragCreates"
      ::= {ipv6StatsInfo 22}

-- ICMP IPv6 Stats Info

   icmpV6TxMsgs OBJECT-TYPE
     SYNTAX      Counter32
     MAX-ACCESS  read-only
     STATUS      current
     DESCRIPTION
               "TxMsgs"
     ::= {icmpv6StatsInfo 1}

   icmpV6TxErrors OBJECT-TYPE
     SYNTAX      Counter32
     MAX-ACCESS  read-only
     STATUS      current
     DESCRIPTION
               "TxErrors"
     ::= {icmpv6StatsInfo 2}

   icmpV6TxDestUnreachs OBJECT-TYPE
     SYNTAX      Counter32
     MAX-ACCESS  read-only
     STATUS      current
     DESCRIPTION
               "TxDestUnreachs"
     ::= {icmpv6StatsInfo 3}

   icmpV6TxPktTooBigs OBJECT-TYPE
     SYNTAX      Counter32
     MAX-ACCESS  read-only
     STATUS      current
     DESCRIPTION
               "TxPktTooBigs"
     ::= {icmpv6StatsInfo 4}

   icmpV6TxTimeExcds OBJECT-TYPE
     SYNTAX      Counter32
     MAX-ACCESS  read-only
     STATUS      current
     DESCRIPTION
               "TxTimeExcds"
     ::= {icmpv6StatsInfo 5}

   icmpV6TxParmProblems OBJECT-TYPE
     SYNTAX      Counter32
     MAX-ACCESS  read-only
     STATUS      current
     DESCRIPTION
               "TxParmProblems"
     ::= {icmpv6StatsInfo 6}

   icmpV6TxEchos OBJECT-TYPE
     SYNTAX      Counter32
     MAX-ACCESS  read-only
     STATUS      current
     DESCRIPTION
               "TxEchos"
     ::= {icmpv6StatsInfo 7}

   icmpV6TxEchoReplies OBJECT-TYPE
     SYNTAX      Counter32
     MAX-ACCESS  read-only
     STATUS      current
     DESCRIPTION
               "TxEchoReplies"
     ::= {icmpv6StatsInfo 8}

   icmpV6TxGroupMembQueries OBJECT-TYPE
     SYNTAX      Counter32
     MAX-ACCESS  read-only
     STATUS      current
     DESCRIPTION
               "TxGroupMembQueries"
     ::= {icmpv6StatsInfo 9}

   icmpV6TxGroupMembResponses OBJECT-TYPE
     SYNTAX      Counter32
     MAX-ACCESS  read-only
     STATUS      current
     DESCRIPTION
               "TxGroupMembResponses"
     ::= {icmpv6StatsInfo 10}

   icmpV6TxGroupMembReductions OBJECT-TYPE
     SYNTAX      Counter32
     MAX-ACCESS  read-only
     STATUS      current
     DESCRIPTION
               "TxGroupMembReductions"
     ::= {icmpv6StatsInfo 11}

   icmpV6TxRouterSolicits OBJECT-TYPE
     SYNTAX      Counter32
     MAX-ACCESS  read-only
     STATUS      current
     DESCRIPTION
               "TxRouterSolicits"
     ::= {icmpv6StatsInfo 12}

   icmpV6TxRouterAdvertisements OBJECT-TYPE
     SYNTAX      Counter32
     MAX-ACCESS  read-only
     STATUS      current
     DESCRIPTION
               "TxRouterAdvertisements"
     ::= {icmpv6StatsInfo 13}

   icmpV6TxNeighborSolicits OBJECT-TYPE
     SYNTAX      Counter32
     MAX-ACCESS  read-only
     STATUS      current
     DESCRIPTION
               "TxNeighborSolicits"
     ::= {icmpv6StatsInfo 14}

   icmpV6TxNeighborAdvertisements OBJECT-TYPE
     SYNTAX      Counter32
     MAX-ACCESS  read-only
     STATUS      current
     DESCRIPTION
               "TxNeighborAdvertisements"
     ::= {icmpv6StatsInfo 15}

   icmpV6TxRedirects OBJECT-TYPE
     SYNTAX      Counter32
     MAX-ACCESS  read-only
     STATUS      current
     DESCRIPTION
               "TxRedirects"
     ::= {icmpv6StatsInfo 16}

   icmpV6RxMsgs OBJECT-TYPE
     SYNTAX      Counter32
     MAX-ACCESS  read-only
     STATUS      current
     DESCRIPTION
               "RxMsgs"
     ::= {icmpv6StatsInfo 17}

   icmpV6RxDestUnreachs OBJECT-TYPE
     SYNTAX      Counter32
     MAX-ACCESS  read-only
     STATUS      current
     DESCRIPTION
               "RxDestUnreachs"
     ::= {icmpv6StatsInfo 18}

   icmpV6RxPktTooBigs OBJECT-TYPE
     SYNTAX      Counter32
     MAX-ACCESS  read-only
     STATUS      current
     DESCRIPTION
               "RxPktTooBigs"
     ::= {icmpv6StatsInfo 19}

   icmpV6RxTimeExcds OBJECT-TYPE
     SYNTAX      Counter32
     MAX-ACCESS  read-only
     STATUS      current
     DESCRIPTION
               "RxTimeExcds"
     ::= {icmpv6StatsInfo 20}

   icmpV6RxParmProblems OBJECT-TYPE
     SYNTAX      Counter32
     MAX-ACCESS  read-only
     STATUS      current
     DESCRIPTION
               "RxParmProblems"
     ::= {icmpv6StatsInfo 21}

   icmpV6RxEchoReplies OBJECT-TYPE
     SYNTAX      Counter32
     MAX-ACCESS  read-only
     STATUS      current
     DESCRIPTION
               "RxEchoReplies"
     ::= {icmpv6StatsInfo 22}

   icmpV6RxRouterSolicits OBJECT-TYPE
     SYNTAX      Counter32
     MAX-ACCESS  read-only
     STATUS      current
     DESCRIPTION
               "RxRouterSolicits"
     ::= {icmpv6StatsInfo 23}

   icmpV6RxNeighborSolicits OBJECT-TYPE
     SYNTAX      Counter32
     MAX-ACCESS  read-only
     STATUS      current
     DESCRIPTION
               "RxNeighborSolicits"
     ::= {icmpv6StatsInfo 24}

   icmpV6RxNeighborAdvertisements OBJECT-TYPE
     SYNTAX      Counter32
     MAX-ACCESS  read-only
     STATUS      current
     DESCRIPTION
               "RxNeighborAdvertisements"
     ::= {icmpv6StatsInfo 25}

   icmpV6RxRedirects OBJECT-TYPE
     SYNTAX      Counter32
     MAX-ACCESS  read-only
     STATUS      current
     DESCRIPTION
               "RxRedirects"
     ::= {icmpv6StatsInfo 26}

   icmpV6RxGroupMembResponses OBJECT-TYPE
     SYNTAX      Counter32
     MAX-ACCESS  read-only
     STATUS      current
     DESCRIPTION
               "RxGroupMembResponses"
     ::= {icmpv6StatsInfo 27}

   icmpV6RxGroupMembReductions OBJECT-TYPE
     SYNTAX      Counter32
     MAX-ACCESS  read-only
     STATUS      current
     DESCRIPTION
               "RxGroupMembReductions"
     ::= {icmpv6StatsInfo 28}

-- UDP IPv6 Stats Info

   udpV6RxDatagrams OBJECT-TYPE
     SYNTAX      Counter32
     MAX-ACCESS  read-only
     STATUS      current
     DESCRIPTION
               "udpV6RxDatagrams"
     ::= {udpv6StatsInfo 1}

   udpV6noPorts OBJECT-TYPE
     SYNTAX      Counter32
     MAX-ACCESS  read-only
     STATUS      current
     DESCRIPTION
               "udpV6noPorts"
     ::= {udpv6StatsInfo 2}

   udpV6RxErrors OBJECT-TYPE
     SYNTAX      Counter32
     MAX-ACCESS  read-only
     STATUS      current
     DESCRIPTION
               "udpV6RxErrors"
     ::= {udpv6StatsInfo 3}

   udpV6TxDatagrams OBJECT-TYPE
     SYNTAX      Counter32
     MAX-ACCESS  read-only
     STATUS      current
     DESCRIPTION
               "udpV6TxDatagrams"
     ::= {udpv6StatsInfo 4}

-- TCP Conn IPv6 Stats

  tcpConnv6Table OBJECT-TYPE
      SYNTAX      SEQUENCE OF TcpConnv6Entry
      MAX-ACCESS  not-accessible
      STATUS      current
      DESCRIPTION
              "The rip info table."
      ::= { tcpConnv6StatsInfo 1 }

  tcpConnv6Entry OBJECT-TYPE
      SYNTAX      TcpConnv6Entry
      MAX-ACCESS  not-accessible
      STATUS      current
      DESCRIPTION
              "An entry in the tcpConnv6Table"
      INDEX   { tcpConnv6Index }
      ::= { tcpConnv6Table 1 }

  TcpConnv6Entry ::=
      SEQUENCE {
        tcpConnv6Index              GenericTableIndex,
        tcpConnv6LocalAddress            DisplayString,
        tcpConnv6LocalPort            Integer32,
        tcpConnv6RemoteAddress            DisplayString,
        tcpConnv6RemotePort            Integer32,
        tcpConnv6TxQueueBytes            Counter32,
        tcpConnv6RxQueueBytes            Counter32,
        tcpConnv6State            INTEGER
        }

  tcpConnv6Index OBJECT-TYPE
      SYNTAX      GenericTableIndex
      MAX-ACCESS  not-accessible
      STATUS      current
      DESCRIPTION
              "Index"
      ::= { tcpConnv6Entry 1 }

  tcpConnv6LocalAddress OBJECT-TYPE
      SYNTAX      DisplayString
      MAX-ACCESS  read-only
      STATUS      current
      DESCRIPTION
              "LocalAddress"
      ::= { tcpConnv6Entry 2}

  tcpConnv6LocalPort OBJECT-TYPE
      SYNTAX      Integer32(0..65535)
      MAX-ACCESS  read-only
      STATUS      current
      DESCRIPTION
              "LocalPort"
      ::= { tcpConnv6Entry 3}

  tcpConnv6RemoteAddress OBJECT-TYPE
      SYNTAX      DisplayString
      MAX-ACCESS  read-only
      STATUS      current
      DESCRIPTION
              "RemoteAddress"
      ::= { tcpConnv6Entry 4}

  tcpConnv6RemotePort OBJECT-TYPE
      SYNTAX      Integer32(0..65535)
      MAX-ACCESS  read-only
      STATUS      current
      DESCRIPTION
              "RemotePort"
      ::= { tcpConnv6Entry 5}

  tcpConnv6TxQueueBytes OBJECT-TYPE
      SYNTAX      Counter32
      MAX-ACCESS  read-only
      STATUS      current
      DESCRIPTION
              "tcpConnv6TxQueueBytes"
      ::= { tcpConnv6Entry 6}

  tcpConnv6RxQueueBytes OBJECT-TYPE
      SYNTAX      Counter32
      MAX-ACCESS  read-only
      STATUS      current
      DESCRIPTION
              "tcpConnv6RxQueueBytes"
      ::= { tcpConnv6Entry 7}

  tcpConnv6State OBJECT-TYPE
      SYNTAX      INTEGER {
        established(1),
        synSent(2),
        synRecv(3),
        finWait1(4),
        finWait2(5),
        timeWait(6),
        close(7),
        closeWait(8),
        lastAck(9),
        listen(10),
        closing(11)
      }
      MAX-ACCESS  read-only
      STATUS      current
      DESCRIPTION
              "State"
      ::= { tcpConnv6Entry 8}

-- UDP Conn IPv6 Stats

  udpConnv6Table OBJECT-TYPE
      SYNTAX      SEQUENCE OF UdpConnv6Entry
      MAX-ACCESS  not-accessible
      STATUS      current
      DESCRIPTION
              "udpConnv6Table"
      ::= { udpConnv6StatsInfo 1 }

  udpConnv6Entry OBJECT-TYPE
      SYNTAX      UdpConnv6Entry
      MAX-ACCESS  not-accessible
      STATUS      current
      DESCRIPTION
              "An entry in the udpConnv6Table"
      INDEX   { udpConnv6Index }
      ::= { udpConnv6Table 1 }

  UdpConnv6Entry ::=
      SEQUENCE {
        udpConnv6Index              GenericTableIndex,
        udpConnv6LocalAddress       DisplayString,
        udpConnv6LocalPort          Integer32,
        udpConnv6RemoteAddress      DisplayString,
        udpConnv6RemotePort         Integer32,
        udpConnv6TxQueueBytes       Counter32,
        udpConnv6RxQueueBytes       Counter32,
        udpConnv6State              INTEGER
        }

  udpConnv6Index OBJECT-TYPE
      SYNTAX      GenericTableIndex
      MAX-ACCESS  not-accessible
      STATUS      current
      DESCRIPTION
              "Index"
      ::= { udpConnv6Entry 1 }

  udpConnv6LocalAddress OBJECT-TYPE
      SYNTAX      DisplayString
      MAX-ACCESS  read-only
      STATUS      current
      DESCRIPTION
              "LocalAddress"
      ::= { udpConnv6Entry 2}

  udpConnv6LocalPort OBJECT-TYPE
      SYNTAX      Integer32(0..65535)
      MAX-ACCESS  read-only
      STATUS      current
      DESCRIPTION
              "LocalPort"
      ::= { udpConnv6Entry 3}

  udpConnv6RemoteAddress OBJECT-TYPE
      SYNTAX      DisplayString
      MAX-ACCESS  read-only
      STATUS      current
      DESCRIPTION
              "RemoteAddress"
      ::= { udpConnv6Entry 4}

  udpConnv6RemotePort OBJECT-TYPE
      SYNTAX      Integer32(0..65535)
      MAX-ACCESS  read-only
      STATUS      current
      DESCRIPTION
              "RemotePort"
      ::= { udpConnv6Entry 5}

  udpConnv6TxQueueBytes OBJECT-TYPE
      SYNTAX      Counter32
      MAX-ACCESS  read-only
      STATUS      current
      DESCRIPTION
              "TxQueue"
      ::= { udpConnv6Entry 6}

  udpConnv6RxQueueBytes OBJECT-TYPE
      SYNTAX      Counter32
      MAX-ACCESS  read-only
      STATUS      current
      DESCRIPTION
              "RxQueue"
      ::= { udpConnv6Entry 7}

  udpConnv6State OBJECT-TYPE
      SYNTAX      INTEGER {
          established(1)
      }
      MAX-ACCESS  read-only
      STATUS      current
      DESCRIPTION
              "State"
      ::= { udpConnv6Entry 8}

-- Route IPv6 Stats

  routev6Table OBJECT-TYPE
      SYNTAX      SEQUENCE OF Routev6Entry
      MAX-ACCESS  not-accessible
      STATUS      current
      DESCRIPTION
              "The route IPv6 info table."
      ::= { routev6Info 1 }

  routev6Entry OBJECT-TYPE
      SYNTAX      Routev6Entry
      MAX-ACCESS  not-accessible
      STATUS      current
      DESCRIPTION
              "An entry in the route IPv6 Table"
      INDEX   { routev6Index }
      ::= { routev6Table 1 }

  Routev6Entry ::=
      SEQUENCE {
        routev6Index          GenericTableIndex,
        routev6Destination    DisplayString,
        routev6PrefixBits     Integer32,
        routev6Gateway        DisplayString,
        routev6Metric         Integer32,
        routev6Flags          DisplayString,
        routev6Interface      DisplayString
        }

  routev6Index OBJECT-TYPE
      SYNTAX      GenericTableIndex
      MAX-ACCESS  not-accessible
      STATUS      current
      DESCRIPTION
              "Index"
      ::= { routev6Entry 1 }

  routev6Destination OBJECT-TYPE
      SYNTAX      DisplayString
      MAX-ACCESS  read-only
      STATUS      current
      DESCRIPTION
              "Destination"
      ::= { routev6Entry 2}

  routev6PrefixBits OBJECT-TYPE
      SYNTAX      Integer32(0..128)
      MAX-ACCESS  read-only
      STATUS      current
      DESCRIPTION
              "PrefixBits"
      ::= { routev6Entry 3}

  routev6Gateway OBJECT-TYPE
      SYNTAX      DisplayString
      MAX-ACCESS  read-only
      STATUS      current
      DESCRIPTION
              "Gateway"
      ::= { routev6Entry 4}

  routev6Metric OBJECT-TYPE
      SYNTAX      Integer32(1..15)
      MAX-ACCESS  read-only
      STATUS      current
      DESCRIPTION
              "Metric"
      ::= { routev6Entry 5}

  routev6Flags OBJECT-TYPE
      SYNTAX      DisplayString
      MAX-ACCESS  read-only
      STATUS      current
      DESCRIPTION
              "Flags"
      ::= { routev6Entry 6}

  routev6Interface OBJECT-TYPE
      SYNTAX      DisplayString
      MAX-ACCESS  read-only
      STATUS      current
      DESCRIPTION
              "Interface"
      ::= { routev6Entry 7}

-- Rip (V6) Info

  ripv6InfoTable OBJECT-TYPE
      SYNTAX      SEQUENCE OF Ripv6InfoEntry
      MAX-ACCESS  not-accessible
      STATUS      current
      DESCRIPTION
              "The ripv6 info table."
      ::= { ripv6TableInfo 1 }

  ripv6InfoEntry OBJECT-TYPE
      SYNTAX      Ripv6InfoEntry
      MAX-ACCESS  not-accessible
      STATUS      current
      DESCRIPTION
              "An entry in the ripv6InfoTable, each relating to a ripv6 entry."
      INDEX   { ripv6Index }
      ::= { ripv6InfoTable 1 }

  Ripv6InfoEntry ::=
      SEQUENCE {
        ripv6Index              GenericTableIndex,
        ripv6TableIpAddr              IpAddress,
        ripv6TableLastUpdate            Unsigned32,
        ripv6TableBadPackets            Counter32,
        ripv6TableBadRoutes            Counter32
      }

  ripv6Index OBJECT-TYPE
      SYNTAX      GenericTableIndex
      MAX-ACCESS  not-accessible
      STATUS      current
      DESCRIPTION
              "The table entry number for this ripv6."
      ::= { ripv6InfoEntry 1 }

  ripv6TableIpAddr OBJECT-TYPE
      SYNTAX      IpAddress
      MAX-ACCESS  read-only
      STATUS      current
      DESCRIPTION
              "ripv6IpAddr"
      ::= { ripv6InfoEntry 2 }

  ripv6TableLastUpdate OBJECT-TYPE
      SYNTAX      Unsigned32
      MAX-ACCESS  read-only
      STATUS      current
      DESCRIPTION
              "Last Update in Seconds"
      ::= { ripv6InfoEntry 3 }


  ripv6TableBadPackets OBJECT-TYPE
      SYNTAX      Counter32
      MAX-ACCESS  read-only
      STATUS      current
      DESCRIPTION
              "Last Update in Seconds"
      ::= { ripv6InfoEntry 4 }

  ripv6TableBadRoutes OBJECT-TYPE
      SYNTAX      Counter32
      MAX-ACCESS  read-only
      STATUS      current
      DESCRIPTION
              "Last Update in Seconds"
      ::= { ripv6InfoEntry 5 }

-- Interface IPv6 Stats

  interfacev6InfoTable OBJECT-TYPE
      SYNTAX      SEQUENCE OF Interfacev6InfoEntry
      MAX-ACCESS  not-accessible
      STATUS      current
      DESCRIPTION
              "The interface IPv6 info table."
      ::= { interfacev6Info 1 }

  interfacev6InfoEntry OBJECT-TYPE
      SYNTAX      Interfacev6InfoEntry
      MAX-ACCESS  not-accessible
      STATUS      current
      DESCRIPTION
              "An entry in the interface IPv6 table"
      INDEX   { interfacev6Index }
      ::= { interfacev6InfoTable 1 }

  Interfacev6InfoEntry ::=
      SEQUENCE {
        interfacev6Index             GenericTableIndex,
        interfacev6Name              DisplayString,
        interfacev6Address           DisplayString,
        interfacev6PrefixBits        Integer32,
        interfacev6Scope             INTEGER
      }

  interfacev6Index OBJECT-TYPE
      SYNTAX      GenericTableIndex
      MAX-ACCESS  not-accessible
      STATUS      current
      DESCRIPTION
              "interfacev6Index"
      ::= { interfacev6InfoEntry 1}

  interfacev6Name OBJECT-TYPE
      SYNTAX      DisplayString
      MAX-ACCESS  read-only
      STATUS      current
      DESCRIPTION
              "interfacev6Name"
      ::= { interfacev6InfoEntry 2}

  interfacev6Address OBJECT-TYPE
      SYNTAX      DisplayString
      MAX-ACCESS  read-only
      STATUS      current
      DESCRIPTION
              "interfacev6Address"
      ::= { interfacev6InfoEntry 3}

  interfacev6PrefixBits OBJECT-TYPE
      SYNTAX      Integer32(0..128)
      MAX-ACCESS  read-only
      STATUS      current
      DESCRIPTION
              "interfacev6PrefixBits"
      ::= { interfacev6InfoEntry 4}

  interfacev6Scope OBJECT-TYPE
      SYNTAX      INTEGER {
        global(1),
        host(2),
        link(3),
        site(4),
        compatv4(5),
        unknown(6)
      }
      MAX-ACCESS  read-only
      STATUS      current
      DESCRIPTION
              "interfacev6Scope"
      ::= { interfacev6InfoEntry 5}

-- SSL Server Info

  sslServerStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {sslInfo 1}

  sslVersion  OBJECT-TYPE
      SYNTAX      INTEGER {
        any(1),
        tlsv1(2),
        sslv3(3)
      }
      MAX-ACCESS    read-write
      STATUS        current
      DESCRIPTION
                "Specify whether you want to use:
                 Any-The Device Server will try a TLSv1 connection first.
                     If that fails, it will try an SSLv3 connection. 
                     If that fails, it will try an SSLv2 connection.
                 TLSv1-The connection will use only TLSv1.
                 SSLv3-The connection will use only SSLv3.
                 The default is Any."
      ::= {sslInfo 2}

  sslType    OBJECT-TYPE
      SYNTAX      INTEGER {
        client(1),
        server(2)
      }
      MAX-ACCESS    read-write
      STATUS        current
      DESCRIPTION
                "Specify whether the Device Server will act as an 
                 SSL/TLS client or server. The default is Client."
      ::= {sslInfo 3}

  sslVerifyPeerCertificate  OBJECT-TYPE
      SYNTAX   OnOffValue
      MAX-ACCESS    read-write
      STATUS        current
      DESCRIPTION
                "Enable this option when you want the Validation Criteria
                 to match the Peer Certificate for authentication to pass.
                 If you enable this option, you need to download an  
                 SSL/TLS certificate authority (CA) list file to the 
                 Device Server. Any values that are entered in the validation
                 criteria must match the peer certificate for an SSL connection;
                 any fields left blank will not be validated against the peer 
                 certificate."
      ::= {sslInfo 4}

  sslCountry    OBJECT-TYPE
      SYNTAX      DisplayString(SIZE(0..2))
      MAX-ACCESS    read-write
      STATUS        current
      DESCRIPTION
                "A two character country code; for example, US."
      ::= {sslInfo 5}

  sslStateProv    OBJECT-TYPE
      SYNTAX      DisplayString(SIZE(0..128))
      MAX-ACCESS    read-write
      STATUS        current
      DESCRIPTION
                "Up to a 128 character entry for the state/province;
                 for example, IL."
      ::= {sslInfo 6}

  sslLocality    OBJECT-TYPE
      SYNTAX      DisplayString(SIZE(0..128))
      MAX-ACCESS    read-write
      STATUS        current
      DESCRIPTION
                "Up to a 128 character entry for the location; 
                 for example, a city."
      ::= {sslInfo 7}

  sslOrganisation    OBJECT-TYPE
      SYNTAX      DisplayString(SIZE(0..64))
      MAX-ACCESS    read-write
      STATUS        current
      DESCRIPTION
                "Up to a 64 character entry for the organization; 
                 for example, Accounting."
      ::= {sslInfo 8}

  sslOrganisationUnit    OBJECT-TYPE
      SYNTAX      DisplayString(SIZE(0..64))
      MAX-ACCESS    read-write
      STATUS        current
      DESCRIPTION
                "Up to a 64 character entry for the unit in the 
                 organization; for example, Payroll."
      ::= {sslInfo 9}

  sslCommonName    OBJECT-TYPE
      SYNTAX      DisplayString(SIZE(0..64))
      MAX-ACCESS    read-write
      STATUS        current
      DESCRIPTION
                "Up to a 64 character entry for common name; for example,
                 the host name or fully qualified domain name."
      ::= {sslInfo 10}

  sslEmail    OBJECT-TYPE
      SYNTAX      DisplayString(SIZE(0..128))
      MAX-ACCESS    read-write
      STATUS        current
      DESCRIPTION
                "Up to a 64 character entry for an email address; 
                 for example, acct@anycompany.com."
      ::= {sslInfo 11}

-- SSL Server Cipher Table

  sslCipherTable OBJECT-TYPE
      SYNTAX      SEQUENCE OF SslCipherEntry
      MAX-ACCESS  not-accessible
      STATUS      current
      DESCRIPTION
              "SSL CIpher."
      ::= {sslInfo 12}

  sslCipherEntry OBJECT-TYPE
      SYNTAX      SslCipherEntry
      MAX-ACCESS  not-accessible
      STATUS      current
      DESCRIPTION
              "An entry in the sslCipherTable, each relating to a cipher entry."
      INDEX   { sslCipherPriority }
      ::= { sslCipherTable 1 }

  SslCipherEntry ::=
      SEQUENCE {
  sslCipherPriority       Integer32,
  sslCipherStatus        ContainerStatus,
  sslCipherEncryption        INTEGER,
  sslCipherKeySizeMin        INTEGER,
  sslCipherKeySizeMax        INTEGER,
  sslCipherKeyExchange        INTEGER,
  sslCipherHMAC        INTEGER
      }

  sslCipherPriority OBJECT-TYPE
      SYNTAX      Integer32(1..5)
      MAX-ACCESS  not-accessible
      STATUS      current
      DESCRIPTION
              "The cipher priority. 1- highest 5 - lowest."
      ::= { sslCipherEntry 1 }

  sslCipherStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { sslCipherEntry 2 }

  sslCipherEncryption OBJECT-TYPE
      SYNTAX      INTEGER {
        none(1),
        any(2),
        aes(3),
        tripledes(4),
        des(5),
        arctwo(6),
        arcfour(7)
      }
      MAX-ACCESS  read-write
      STATUS      current
      DESCRIPTION
              "SSL Encryption. None is not allowed for priority 1.
               Any will use the first encryption format that can be 
               negotiated. The default is any."
      ::= { sslCipherEntry 3 }

  sslCipherKeySizeMin OBJECT-TYPE
      SYNTAX      INTEGER {
        min40(1),
        min56(2),
        min64(3),
        min128(4),
        min168(5),
        min256(6)
      }
      MAX-ACCESS  read-write
      STATUS      current
      DESCRIPTION
              "The minimum key size value that will be used for 
               the specified encryption type. The default is 40."
      ::= { sslCipherEntry 4 }

  sslCipherKeySizeMax OBJECT-TYPE
      SYNTAX      INTEGER {
        max40(1),
        max56(2),
        max64(3),
        max128(4),
        max168(5),
        max256(6)
      }
      MAX-ACCESS  read-write
      STATUS      current
      DESCRIPTION
              "The maximum key size value that will be used for the
               specified encryption type. The default is 256."
      ::= { sslCipherEntry 5 }

  sslCipherKeyExchange OBJECT-TYPE
      SYNTAX      INTEGER {
        any(1),
        rsa(2),
        edhrsa(3),
        edhdss(4),
        adh(5) 
      }
      MAX-ACCESS  read-write
      STATUS      current
      DESCRIPTION
              "The type of key to exchange for the encryption format:
               Any-Any key exchange that is valid is used (this does 
                   not, however, include ADH keys).
               RSA-This is an RSA key exchange using an RSA key and 
                   certificate.
               EDHRSA-This is an EDH key exchange using an RSA key 
                   and certificate.
               EDHDSS-This is an EDH key exchange using a DSA key
                   and certificate.
               ADH-This is an anonymous key exchange which does not 
                   require a private key or certificate. Choose this 
                   key if you do not want to authenticate the peer device, 
                   but you want the data encrypted on the SSL/TLS connection.
               The default is Any."
      ::= { sslCipherEntry 6 }

  sslCipherHMAC OBJECT-TYPE
      SYNTAX      INTEGER {
        any(1),
        sha(2),
        md5(3)
      }
      MAX-ACCESS  read-write
      STATUS      current
      DESCRIPTION
              "Select the key-hashing for message authentication method 
               for your encryption type: Any, MD5, or SHA1.
               The default is Any."
      ::= { sslCipherEntry 7 }

  
    -- Console Info
   consoleStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {consoleInfo 1}
  
  consoleSpeed OBJECT-TYPE
      SYNTAX      INTEGER {
        b9600(1),
        b19200(2),
        b38400(3),
        b57600(4),
        b115200(5)
      }
      MAX-ACCESS  read-write
      STATUS      current
      DESCRIPTION
              "Specifies the baud rate of the console port; keep in mind that
               speed is affected by the length of the cable."
      ::= { consoleInfo 2}

  consoleFlowControl OBJECT-TYPE
      SYNTAX      INTEGER {
        none(0),
        soft(1),
        hard(2)
      }
      MAX-ACCESS  read-write
      STATUS      current
      DESCRIPTION
              "Defines whether the data flow is handled by the
               software (Soft), hardware (Hard) or None."
      ::= { consoleInfo 3}
  
  consoleMediaType OBJECT-TYPE
      SYNTAX      INTEGER {
        usb(0),
        rj45(1)
      }
      MAX-ACCESS  read-write
      STATUS      current
      DESCRIPTION
              "Defines whether the USB or RJ45 port is used for console input 
              when the device is started."
      ::= { consoleInfo 4}
    
  consoleUsbTimeout OBJECT-TYPE
      SYNTAX      Integer32(0..240) 
      MAX-ACCESS  read-write
      STATUS      current
      DESCRIPTION
              "Defines a inactivity timeout for the USB port. If this expires the
              console function is switched to the RJ45. Actual time out values are
              1-240 minutes plus 0 indicates no timeout."
      ::= { consoleInfo 5}    

-- Modbusgateway Info
   modbusGatewayStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {modbusGatewayInfo 1}
  modbusGatewayConnIdleTimeout OBJECT-TYPE
      SYNTAX      Integer32(0..300)
      MAX-ACCESS  read-write
      STATUS      current
      DESCRIPTION
              "Connection/Idle timeout: 0: never close; 1->300."
      ::= { modbusGatewayInfo 2}

  modbusGatewayException OBJECT-TYPE
      SYNTAX      OnOffValue
      MAX-ACCESS  read-write
      STATUS      current
      DESCRIPTION
              "Enable/disable modbus exception."
      ::= { modbusGatewayInfo 3}

  modbusGatewayCharacterTimeout OBJECT-TYPE
      SYNTAX      Integer32(10..1000)
      MAX-ACCESS  read-write
      STATUS      current
      DESCRIPTION
              "Character timeout."
      ::= { modbusGatewayInfo 4}
	  
  modbusGatewayMessageTimeout OBJECT-TYPE
      SYNTAX      Integer32(10..1000)
      MAX-ACCESS  read-write
      STATUS      current
      DESCRIPTION
              "Message timeout."
      ::= { modbusGatewayInfo 5}
	  
  modbusGatewayPortNumber OBJECT-TYPE
      SYNTAX      Integer32(0..65535)
      MAX-ACCESS  read-write
      STATUS      current
      DESCRIPTION
              "Remote master transport layer (TCP/UDP) port number"
      ::= { modbusGatewayInfo 6}
	  
  modbusGatewayUIDAddressMode OBJECT-TYPE
  SYNTAX      INTEGER{
	  embedded (0),
	  remapped (1)
  }
      MAX-ACCESS  read-write
      STATUS      current
      DESCRIPTION
              "Slave UID address mode."
      ::= { modbusGatewayInfo 7}
	  
  modbusGatewayRemappedUID OBJECT-TYPE
  SYNTAX      Integer32(1..247)
      MAX-ACCESS  read-write
      STATUS      current
      DESCRIPTION
              "Remapped UID under Remapped address mode"
      ::= { modbusGatewayInfo 8}
	  
  modbusGatewayBroadcast OBJECT-TYPE
      SYNTAX      OnOffValue
      MAX-ACCESS  read-write
      STATUS      current
      DESCRIPTION
              "Enable/disable propagate Modbus TCP broadcast requests."
      ::= { modbusGatewayInfo 9}
      
  modbusGatewayNextRequestDelay OBJECT-TYPE
      SYNTAX      Integer32(0..1000)
      MAX-ACCESS  read-write
      STATUS      current
      DESCRIPTION
              "Delay to allow serial slaves to re-enable receivers before issuing next
			   master request."
      ::= { modbusGatewayInfo 10}

  modbusGatewayQueuing OBJECT-TYPE
      SYNTAX      OnOffValue
      MAX-ACCESS  read-write
      STATUS      current
      DESCRIPTION
              "Enable/disable request queuing."
      ::= { modbusGatewayInfo 11}

  modbusGatewaySSL OBJECT-TYPE
      SYNTAX      OnOffValue
      MAX-ACCESS  read-write
      STATUS      current
      DESCRIPTION
              "Enable/disable modbus slave SSL."
      ::= { modbusGatewayInfo 12}

  modbusGatewayIPAliasing OBJECT-TYPE
      SYNTAX      OnOffValue
      MAX-ACCESS  read-write
      STATUS      current
      DESCRIPTION
              "Enable/disable modbus slave IP Aliasing."
      ::= { modbusGatewayInfo 13}


-- Modbus Stats Info

-- Modbus TCP Slave Statistics Table
  modbusSlaveTCPStatsTable OBJECT-TYPE
      SYNTAX      SEQUENCE OF ModbusSlaveTCPStatsEntry
      MAX-ACCESS  not-accessible
      STATUS      current
      DESCRIPTION
              "Modbus TCP Slave Statistics Table."
      ::= { modbusStatsInfo 1 }
      
  modbusSlaveTCPStatsEntry OBJECT-TYPE
      SYNTAX      ModbusSlaveTCPStatsEntry
      MAX-ACCESS  not-accessible
      STATUS      current
      DESCRIPTION
              "An entry in the Modbus/TCP Slave statistics table, each relating to a serial port."
      INDEX   { modbusSlaveTCPStatsPortIndex }
      ::= { modbusSlaveTCPStatsTable 1 }

  ModbusSlaveTCPStatsEntry ::=
      SEQUENCE {
    modbusSlaveTCPStatsPortIndex        GenericTableIndex,
    modbusSlaveTCPStatsSerialMode         INTEGER,
    modbusSlaveTCPStatsSerialFrameErrors  Counter32
      }
      
  modbusSlaveTCPStatsPortIndex OBJECT-TYPE
      SYNTAX      GenericTableIndex
      MAX-ACCESS  not-accessible
      STATUS      current
      DESCRIPTION
              "modbusSlaveTCPStatsPortIndex"
      ::= { modbusSlaveTCPStatsEntry 1}

  modbusSlaveTCPStatsSerialMode OBJECT-TYPE
  SYNTAX      INTEGER {
	  rtu(0),
	  ascii(1)
  }
      MAX-ACCESS  read-only
      STATUS      current
      DESCRIPTION
              "Modbus serial device's mode: 0: RTU; 1: ASCII."
      ::= { modbusSlaveTCPStatsEntry 2}
      
  modbusSlaveTCPStatsSerialFrameErrors OBJECT-TYPE
      SYNTAX      Counter32 
      MAX-ACCESS  read-only
      STATUS      current
      DESCRIPTION
              "Modbus serial port frame errors"
      ::= { modbusSlaveTCPStatsEntry 3}
      

-- Modbus TCP Slave Gateway Statistics Table

  modbusSlaveTCPStatsGatewayTable OBJECT-TYPE
      SYNTAX      SEQUENCE OF ModbusSlaveTCPStatsGatewayEntry
      MAX-ACCESS  not-accessible
      STATUS      current
      DESCRIPTION
              "Modbus TCP Slave Gateway Statistics Table."
      ::= { modbusStatsInfo 6 }
      
  modbusSlaveTCPStatsGatewayEntry OBJECT-TYPE
      SYNTAX      ModbusSlaveTCPStatsGatewayEntry
      MAX-ACCESS  not-accessible
      STATUS      current
      DESCRIPTION
              "An entry in the modbusStatsGatewayTable."
      INDEX   {modbusSlaveTCPStatsGatewayPortIndex, modbusSlaveTCPStatsGatewayUIDIndex }
      ::= { modbusSlaveTCPStatsGatewayTable 1 }

  ModbusSlaveTCPStatsGatewayEntry ::=
      SEQUENCE {
    modbusSlaveTCPStatsGatewayPortIndex        GenericTableIndex,
    modbusSlaveTCPStatsGatewayUIDIndex          Integer32,
    modbusSlaveTCPStatsGatewayRemoteIP          Ipv4v6Address,
    modbusSlaveTCPStatsGatewayUID               Integer32,
    modbusSlaveTCPStatsGatewayRemotePortNumber  Integer32,
    modbusSlaveTCPStatsGatewayCommands          Counter32,
    modbusSlaveTCPStatsGatewayResponses         Counter32,
    modbusSlaveTCPStatsGatewayExceptions        Counter32,
    modbusSlaveTCPStatsGatewayFrameErrors       Counter32
      }

  modbusSlaveTCPStatsGatewayPortIndex OBJECT-TYPE
      SYNTAX      GenericTableIndex
      MAX-ACCESS  not-accessible
      STATUS      current
      DESCRIPTION
              "The port number index"
      ::= { modbusSlaveTCPStatsGatewayEntry 1 }

  modbusSlaveTCPStatsGatewayUIDIndex OBJECT-TYPE
      SYNTAX      Integer32(1..247)
      MAX-ACCESS  not-accessible
      STATUS      current
      DESCRIPTION
              "The UID index"
      ::= { modbusSlaveTCPStatsGatewayEntry 2 }

  modbusSlaveTCPStatsGatewayRemoteIP OBJECT-TYPE
      SYNTAX      Ipv4v6Address
      MAX-ACCESS  read-only
      STATUS      current
      DESCRIPTION
              "The remote slave/master IP address."
      ::= { modbusSlaveTCPStatsGatewayEntry 3 }

  modbusSlaveTCPStatsGatewayUID OBJECT-TYPE
      SYNTAX      Integer32(1..247)
      MAX-ACCESS  read-only
      STATUS      current
      DESCRIPTION
              "The UID."
      ::= { modbusSlaveTCPStatsGatewayEntry 4 }

  modbusSlaveTCPStatsGatewayRemotePortNumber OBJECT-TYPE
      SYNTAX      Integer32(0..65535)
      MAX-ACCESS  read-only
      STATUS      current
      DESCRIPTION
              "The remote TCP/UDP port number."
      ::= { modbusSlaveTCPStatsGatewayEntry 5 }

  modbusSlaveTCPStatsGatewayCommands OBJECT-TYPE
      SYNTAX      Counter32
      MAX-ACCESS  read-only
      STATUS      current
      DESCRIPTION
              "The commands count."
      ::= { modbusSlaveTCPStatsGatewayEntry 6 }
	  
  modbusSlaveTCPStatsGatewayResponses OBJECT-TYPE
      SYNTAX      Counter32
      MAX-ACCESS  read-only
      STATUS      current
      DESCRIPTION
              "The response count."
      ::= { modbusSlaveTCPStatsGatewayEntry 7 }
      
  modbusSlaveTCPStatsGatewayExceptions OBJECT-TYPE
      SYNTAX      Counter32
      MAX-ACCESS  read-only
      STATUS      current
      DESCRIPTION
              "the exceptions count."
      ::= { modbusSlaveTCPStatsGatewayEntry 8 }
      
  modbusSlaveTCPStatsGatewayFrameErrors OBJECT-TYPE
      SYNTAX      Counter32
      MAX-ACCESS  read-only
      STATUS      current
      DESCRIPTION
              "The frame errors count."
      ::= { modbusSlaveTCPStatsGatewayEntry 9 }

-- Modbus TCP Master Statistics Table

  modbusMasterTCPStatsTable OBJECT-TYPE
      SYNTAX      SEQUENCE OF ModbusMasterTCPStatsEntry
      MAX-ACCESS  not-accessible
      STATUS      current
      DESCRIPTION
              "Modbus TCP Master Statistics Table."
      ::= { modbusStatsInfo 2 }
      
  modbusMasterTCPStatsEntry OBJECT-TYPE
      SYNTAX      ModbusMasterTCPStatsEntry
      MAX-ACCESS  not-accessible
      STATUS      current
      DESCRIPTION
              "An entry in the Modbus/TCP Master statistics table, each relating to a serial port."
      INDEX   { modbusMasterTCPStatsPortIndex }
      ::= { modbusMasterTCPStatsTable 1 }

  ModbusMasterTCPStatsEntry ::=
      SEQUENCE {
    modbusMasterTCPStatsPortIndex      GenericTableIndex,
    modbusMasterTCPStatsSerialMode        INTEGER,
    modbusMasterTCPStatsSerialFrameErrors Counter32
     }
      
  modbusMasterTCPStatsPortIndex OBJECT-TYPE
      SYNTAX      GenericTableIndex
      MAX-ACCESS  not-accessible
      STATUS      current
      DESCRIPTION
              "modbusMasterTCPStatsPortIndex"
      ::= { modbusMasterTCPStatsEntry 1}

  modbusMasterTCPStatsSerialMode OBJECT-TYPE
  SYNTAX      INTEGER {
	  rtu(0),
	  ascii(1)
  }
      MAX-ACCESS  read-only
      STATUS      current
      DESCRIPTION
              "Modbus serial device's mode: 0: RTU; 1: ASCII."
      ::= { modbusMasterTCPStatsEntry 2}
      
  modbusMasterTCPStatsSerialFrameErrors OBJECT-TYPE
      SYNTAX      Counter32 
      MAX-ACCESS  read-only
      STATUS      current
      DESCRIPTION
              "Modbus serial port frame errors"
      ::= { modbusMasterTCPStatsEntry 3}


-- Modbus TCP Master Gateway Statistics Table

  modbusMasterTCPStatsGatewayTable OBJECT-TYPE
      SYNTAX      SEQUENCE OF ModbusMasterTCPStatsGatewayEntry
      MAX-ACCESS  not-accessible
      STATUS      current
      DESCRIPTION
              "Modbus Master TCP Gateway Statistics Table."
      ::= { modbusStatsInfo 7 }
      
  modbusMasterTCPStatsGatewayEntry OBJECT-TYPE
      SYNTAX      ModbusMasterTCPStatsGatewayEntry
      MAX-ACCESS  not-accessible
      STATUS      current
      DESCRIPTION
              "An entry in the modbusStatsGatewayTable."
      INDEX   {modbusMasterTCPStatsGatewayPortIndex, modbusMasterTCPStatsGatewayUIDIndex }
      ::= { modbusMasterTCPStatsGatewayTable 1 }

  ModbusMasterTCPStatsGatewayEntry ::=
     SEQUENCE {
  modbusMasterTCPStatsGatewayPortIndex                GenericTableIndex,
        modbusMasterTCPStatsGatewayUIDIndex           Integer32,
        modbusMasterTCPStatsGatewayRemoteIP           Ipv4v6Address,
        modbusMasterTCPStatsGatewayUID                Integer32,
        modbusMasterTCPStatsGatewayRemotePortNumber   Integer32,
        modbusMasterTCPStatsGatewayCommands           Counter32,
        modbusMasterTCPStatsGatewayResponses          Counter32,
        modbusMasterTCPStatsGatewayExceptions         Counter32,
        modbusMasterTCPStatsGatewayFrameErrors        Counter32
     }

  modbusMasterTCPStatsGatewayPortIndex OBJECT-TYPE
      SYNTAX      GenericTableIndex
      MAX-ACCESS  not-accessible
      STATUS      current
      DESCRIPTION
              "The port number index"
      ::= { modbusMasterTCPStatsGatewayEntry 1 }
      
  modbusMasterTCPStatsGatewayUIDIndex OBJECT-TYPE
      SYNTAX      Integer32(1..247)
      MAX-ACCESS  not-accessible
      STATUS      current
      DESCRIPTION
              "The UID index"
      ::= { modbusMasterTCPStatsGatewayEntry 2 }

  modbusMasterTCPStatsGatewayRemoteIP OBJECT-TYPE
      SYNTAX      Ipv4v6Address
      MAX-ACCESS  read-only
      STATUS      current
      DESCRIPTION
              "The remote slave/master IP address."
      ::= { modbusMasterTCPStatsGatewayEntry 3 }

  modbusMasterTCPStatsGatewayUID OBJECT-TYPE
      SYNTAX      Integer32(1..247)
      MAX-ACCESS  read-only
      STATUS      current
      DESCRIPTION
              "The UID."
      ::= { modbusMasterTCPStatsGatewayEntry 4 }

  modbusMasterTCPStatsGatewayRemotePortNumber OBJECT-TYPE
      SYNTAX      Integer32(0..65535)
      MAX-ACCESS  read-only
      STATUS      current
      DESCRIPTION
              "the remote TCP/UDP port number."
      ::= { modbusMasterTCPStatsGatewayEntry 5 }

  modbusMasterTCPStatsGatewayCommands OBJECT-TYPE
      SYNTAX      Counter32
      MAX-ACCESS  read-only
      STATUS      current
      DESCRIPTION
              "The commands count."
      ::= { modbusMasterTCPStatsGatewayEntry 6 }
	  
  modbusMasterTCPStatsGatewayResponses OBJECT-TYPE
      SYNTAX      Counter32
      MAX-ACCESS  read-only
      STATUS      current
      DESCRIPTION
              "The response count."
      ::= { modbusMasterTCPStatsGatewayEntry 7 }
      
  modbusMasterTCPStatsGatewayExceptions OBJECT-TYPE
      SYNTAX      Counter32
      MAX-ACCESS  read-only
      STATUS      current
      DESCRIPTION
              "The exceptions count."
      ::= { modbusMasterTCPStatsGatewayEntry 8 }
      
  modbusMasterTCPStatsGatewayFrameErrors OBJECT-TYPE
      SYNTAX      Counter32
      MAX-ACCESS  read-only
      STATUS      current
      DESCRIPTION
              "The frame errors count."
      ::= { modbusMasterTCPStatsGatewayEntry 9 }


-- Modbus UDP Slave Statistics Table

  modbusSlaveUDPStatsTable OBJECT-TYPE
      SYNTAX      SEQUENCE OF ModbusSlaveUDPStatsEntry
      MAX-ACCESS  not-accessible
      STATUS      current
      DESCRIPTION
              "Modbus UDP Slave Statistics Table."
      ::= { modbusStatsInfo 3 }
      
  modbusSlaveUDPStatsEntry OBJECT-TYPE
      SYNTAX      ModbusSlaveUDPStatsEntry
      MAX-ACCESS  not-accessible
      STATUS      current
      DESCRIPTION
              "An entry in the Modbus/UDP Slave statistics table, each relating to a serial port."
      INDEX   { modbusSlaveUDPStatsPortIndex }
      ::= { modbusSlaveUDPStatsTable 1 }

  ModbusSlaveUDPStatsEntry ::=
     SEQUENCE {
        modbusSlaveUDPStatsPortIndex            GenericTableIndex,
        modbusSlaveUDPStatsSerialMode        INTEGER,
        modbusSlaveUDPStatsSerialFrameErrors Counter32
     }
  modbusSlaveUDPStatsPortIndex OBJECT-TYPE
      SYNTAX      GenericTableIndex
      MAX-ACCESS  not-accessible
      STATUS      current
      DESCRIPTION
              "modbusSlaveUDPStatsPortIndex"
      ::= { modbusSlaveUDPStatsEntry 1}

  modbusSlaveUDPStatsSerialMode OBJECT-TYPE
  SYNTAX      INTEGER {
	  rtu(0),
	  ascii(1)
  }
      MAX-ACCESS  read-only
      STATUS      current
      DESCRIPTION
              "Modbus serial device's mode: 0: RTU; 1: ASCII."
      ::= { modbusSlaveUDPStatsEntry 2}
      
  modbusSlaveUDPStatsSerialFrameErrors OBJECT-TYPE
      SYNTAX      Counter32 
      MAX-ACCESS  read-only
      STATUS      current
      DESCRIPTION
              "Modbus serial port frame errors"
      ::= { modbusSlaveUDPStatsEntry 3}


-- Modbus UDP Slave Gateway Statistics Table

  modbusSlaveUDPStatsGatewayTable OBJECT-TYPE
      SYNTAX      SEQUENCE OF ModbusSlaveUDPStatsGatewayEntry
      MAX-ACCESS  not-accessible
      STATUS      current
      DESCRIPTION
              "Modbus UDP Slave Gateway Statistics Table."
      ::= { modbusStatsInfo 8 }
      
  modbusSlaveUDPStatsGatewayEntry OBJECT-TYPE
      SYNTAX      ModbusSlaveUDPStatsGatewayEntry
      MAX-ACCESS  not-accessible
      STATUS      current
      DESCRIPTION
              "An entry in the modbusStatsGatewayTable."
      INDEX   {modbusSlaveUDPStatsGatewayPortIndex, modbusSlaveUDPStatsGatewayUIDIndex }
      ::= { modbusSlaveUDPStatsGatewayTable 1 }

  ModbusSlaveUDPStatsGatewayEntry ::=
      SEQUENCE {
         modbusSlaveUDPStatsGatewayPortIndex        GenericTableIndex,
         modbusSlaveUDPStatsGatewayUIDIndex           Integer32,
         modbusSlaveUDPStatsGatewayRemoteIP           Ipv4v6Address,
         modbusSlaveUDPStatsGatewayUID                Integer32,
         modbusSlaveUDPStatsGatewayRemotePortNumber   Integer32,
         modbusSlaveUDPStatsGatewayCommands           Counter32,
         modbusSlaveUDPStatsGatewayResponses          Counter32,
         modbusSlaveUDPStatsGatewayExceptions         Counter32,
         modbusSlaveUDPStatsGatewayFrameErrors        Counter32
      }

  modbusSlaveUDPStatsGatewayPortIndex OBJECT-TYPE
      SYNTAX      GenericTableIndex
      MAX-ACCESS  not-accessible
      STATUS      current
      DESCRIPTION
              "The port number index"
      ::= { modbusSlaveUDPStatsGatewayEntry 1 }
   
  modbusSlaveUDPStatsGatewayUIDIndex OBJECT-TYPE
      SYNTAX      Integer32(1..247)
      MAX-ACCESS  not-accessible
      STATUS      current
      DESCRIPTION
              "The UID index"
      ::= { modbusSlaveUDPStatsGatewayEntry 2 }

  modbusSlaveUDPStatsGatewayRemoteIP OBJECT-TYPE
      SYNTAX      Ipv4v6Address
      MAX-ACCESS  read-only
      STATUS      current
      DESCRIPTION
              "The remote slave/master IP address."
      ::= { modbusSlaveUDPStatsGatewayEntry 3 }

  modbusSlaveUDPStatsGatewayUID OBJECT-TYPE
      SYNTAX      Integer32(1..247)
      MAX-ACCESS  read-only
      STATUS      current
      DESCRIPTION
              "The UID."
      ::= { modbusSlaveUDPStatsGatewayEntry 4 }

  modbusSlaveUDPStatsGatewayRemotePortNumber OBJECT-TYPE
      SYNTAX      Integer32(0..65535)
      MAX-ACCESS  read-only
      STATUS      current
      DESCRIPTION
              "the remote TCP/UDP port number."
      ::= { modbusSlaveUDPStatsGatewayEntry 5 }

  modbusSlaveUDPStatsGatewayCommands OBJECT-TYPE
      SYNTAX      Counter32
      MAX-ACCESS  read-only
      STATUS      current
      DESCRIPTION
              "The commands count."
      ::= { modbusSlaveUDPStatsGatewayEntry 6 }
	  
  modbusSlaveUDPStatsGatewayResponses OBJECT-TYPE
      SYNTAX      Counter32
      MAX-ACCESS  read-only
      STATUS      current
      DESCRIPTION
              "The response count."
      ::= { modbusSlaveUDPStatsGatewayEntry 7 }
      
  modbusSlaveUDPStatsGatewayExceptions OBJECT-TYPE
      SYNTAX      Counter32
      MAX-ACCESS  read-only
      STATUS      current
      DESCRIPTION
              "The exceptions count."
      ::= { modbusSlaveUDPStatsGatewayEntry 8 }
      
  modbusSlaveUDPStatsGatewayFrameErrors OBJECT-TYPE
      SYNTAX      Counter32
      MAX-ACCESS  read-only
      STATUS      current
      DESCRIPTION
              "The frame errors count."
      ::= { modbusSlaveUDPStatsGatewayEntry 9 }

-- Modbus UDP Master Statistics Table

  modbusMasterUDPStatsTable OBJECT-TYPE
      SYNTAX      SEQUENCE OF ModbusMasterUDPStatsEntry
      MAX-ACCESS  not-accessible
      STATUS      current
      DESCRIPTION
              "Modbus UDP Master Statistics Table."
      ::= { modbusStatsInfo 4 }
      
  modbusMasterUDPStatsEntry OBJECT-TYPE
      SYNTAX      ModbusMasterUDPStatsEntry
      MAX-ACCESS  not-accessible
      STATUS      current
      DESCRIPTION
              "An entry in the Modbus/UDP Master statistics table, each relating to a serial port."
      INDEX   { modbusMasterUDPStatsPortIndex }
      ::= { modbusMasterUDPStatsTable 1 }

  ModbusMasterUDPStatsEntry ::=
      SEQUENCE {
    modbusMasterUDPStatsPortIndex      GenericTableIndex,
    modbusMasterUDPStatsSerialMode        INTEGER,
    modbusMasterUDPStatsSerialFrameErrors Counter32
  }
      
  modbusMasterUDPStatsPortIndex OBJECT-TYPE
      SYNTAX      GenericTableIndex
      MAX-ACCESS  not-accessible
      STATUS      current
      DESCRIPTION
              "modbusMasterUDPStatsPortIndex"
      ::= { modbusMasterUDPStatsEntry 1}

  modbusMasterUDPStatsSerialMode OBJECT-TYPE
  SYNTAX      INTEGER {
	  rtu(0),
	  ascii(1)
  }
      MAX-ACCESS  read-only
      STATUS      current
      DESCRIPTION
              "Modbus serial device's mode: 0: RTU; 1: ASCII."
      ::= { modbusMasterUDPStatsEntry 2}
      
  modbusMasterUDPStatsSerialFrameErrors OBJECT-TYPE
      SYNTAX      Counter32 
      MAX-ACCESS  read-only
      STATUS      current
      DESCRIPTION
              "Modbus serial port frame errors"
      ::= { modbusMasterUDPStatsEntry 3}
      

-- Modbus UDP Master Gateway Statistics Table

  modbusMasterUDPStatsGatewayTable OBJECT-TYPE
      SYNTAX      SEQUENCE OF ModbusMasterUDPStatsGatewayEntry
      MAX-ACCESS  not-accessible
      STATUS      current
      DESCRIPTION
              "Modbus UDP Master Gateway Statistics Table."
      ::= { modbusStatsInfo 9 }
      
  modbusMasterUDPStatsGatewayEntry OBJECT-TYPE
      SYNTAX      ModbusMasterUDPStatsGatewayEntry
      MAX-ACCESS  not-accessible
      STATUS      current
      DESCRIPTION
              "An entry in the modbusStatsGatewayTable."
      INDEX   {modbusMasterUDPStatsGatewayPortIndex, modbusMasterUDPStatsGatewayUIDIndex }
      ::= { modbusMasterUDPStatsGatewayTable 1 }

  ModbusMasterUDPStatsGatewayEntry ::=
      SEQUENCE {
  modbusMasterUDPStatsGatewayPortIndex        GenericTableIndex,
  modbusMasterUDPStatsGatewayUIDIndex           Integer32,
  modbusMasterUDPStatsGatewayRemoteIP           Ipv4v6Address,
  modbusMasterUDPStatsGatewayUID                Integer32,
  modbusMasterUDPStatsGatewayRemotePortNumber   Integer32,
  modbusMasterUDPStatsGatewayCommands           Counter32,
  modbusMasterUDPStatsGatewayResponses          Counter32,
  modbusMasterUDPStatsGatewayExceptions         Counter32,
  modbusMasterUDPStatsGatewayFrameErrors        Counter32
  }

  modbusMasterUDPStatsGatewayPortIndex OBJECT-TYPE
      SYNTAX      GenericTableIndex
      MAX-ACCESS  not-accessible
      STATUS      current
      DESCRIPTION
              "The port number index"
      ::= { modbusMasterUDPStatsGatewayEntry 1 }
   
  modbusMasterUDPStatsGatewayUIDIndex OBJECT-TYPE
      SYNTAX      Integer32(1..247)
      MAX-ACCESS  not-accessible
      STATUS      current
      DESCRIPTION
              "The UID index"
      ::= { modbusMasterUDPStatsGatewayEntry 2 }

  modbusMasterUDPStatsGatewayRemoteIP OBJECT-TYPE
      SYNTAX      Ipv4v6Address
      MAX-ACCESS  read-only
      STATUS      current
      DESCRIPTION
              "The remote slave/master IP address."
      ::= { modbusMasterUDPStatsGatewayEntry 3 }

  modbusMasterUDPStatsGatewayUID OBJECT-TYPE
      SYNTAX      Integer32(1..247)
      MAX-ACCESS  read-only
      STATUS      current
      DESCRIPTION
              "The UID."
      ::= { modbusMasterUDPStatsGatewayEntry 4 }

  modbusMasterUDPStatsGatewayRemotePortNumber OBJECT-TYPE
      SYNTAX      Integer32(0..65535)
      MAX-ACCESS  read-only
      STATUS      current
      DESCRIPTION
              "The remote TCP/UDP port number."
      ::= { modbusMasterUDPStatsGatewayEntry 5 }

  modbusMasterUDPStatsGatewayCommands OBJECT-TYPE
      SYNTAX      Counter32
      MAX-ACCESS  read-only
      STATUS      current
      DESCRIPTION
              "The commands count."
      ::= { modbusMasterUDPStatsGatewayEntry 6 }
	  
  modbusMasterUDPStatsGatewayResponses OBJECT-TYPE
      SYNTAX      Counter32
      MAX-ACCESS  read-only
      STATUS      current
      DESCRIPTION
              "The response count."
      ::= { modbusMasterUDPStatsGatewayEntry 7 }
      
  modbusMasterUDPStatsGatewayExceptions OBJECT-TYPE
      SYNTAX      Counter32
      MAX-ACCESS  read-only
      STATUS      current
      DESCRIPTION
              "The exceptions count."
      ::= { modbusMasterUDPStatsGatewayEntry 8 }
      
  modbusMasterUDPStatsGatewayFrameErrors OBJECT-TYPE
      SYNTAX      Counter32
      MAX-ACCESS  read-only
      STATUS      current
      DESCRIPTION
              "The frame errors count."
      ::= { modbusMasterUDPStatsGatewayEntry 9 }

  ioModbusSlaveStats OBJECT IDENTIFIER ::= { modbusStatsInfo 5 }          
  ioModbusSlaveStatsServiceMode OBJECT-TYPE
      SYNTAX      OnOffValue
      MAX-ACCESS  read-only
      STATUS      current
      DESCRIPTION
              "Indicates whether I/O Modbus service is active"
      ::= { ioModbusSlaveStats 1 }

  ioModbusSlaveStatsUid OBJECT-TYPE
      SYNTAX      Integer32(0..255)
      MAX-ACCESS  read-only
      STATUS      current
      DESCRIPTION
              "I/O Modbus Slave UID"
      ::= { ioModbusSlaveStats 2 }
      
  ioModbusSlaveStatsCommands OBJECT-TYPE
      SYNTAX      Counter32
      MAX-ACCESS  read-only
      STATUS      current
      DESCRIPTION
              "I/O Modbus Slave Commands"
      ::= { ioModbusSlaveStats 3 }
      
  ioModbusSlaveStatsResponses OBJECT-TYPE
      SYNTAX      Counter32
      MAX-ACCESS  read-only
      STATUS      current
      DESCRIPTION
              "I/O Modbus Slave Responses"
      ::= { ioModbusSlaveStats 4 }
      
  ioModbusSlaveStatsExceptions OBJECT-TYPE
      SYNTAX      Counter32
      MAX-ACCESS  read-only
      STATUS      current
      DESCRIPTION
              "I/O Modbus Slave Exceptions"
      ::= { ioModbusSlaveStats 5 }
      

  --  customAppServerInfo group.

  customAppServerStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { customAppServerInfo 1 }

  customAppServerCommand OBJECT-TYPE
      SYNTAX      DisplayString(SIZE(1..80))
      MAX-ACCESS  read-write
      STATUS      current
      DESCRIPTION
              "The command line for custom application."
      ::= { customAppServerInfo 2 }



-- I/O info BEGINS  

ioGlobalCfg          OBJECT IDENTIFIER ::= { ioInfo 1 }
ioChannelInfo        OBJECT IDENTIFIER ::= { ioInfo 2 }

ioChannelCfg         OBJECT IDENTIFIER ::= { ioChannelInfo 1 }
ioChannelStatus      OBJECT IDENTIFIER ::= { ioChannelInfo 2 }


  -- I/O global config BEGINS
  ioGlobalCfgStatus OBJECT-TYPE
      SYNTAX      INTEGER {
        configUnchanged(1),
        configChanged(2),
        submitChanges(4),
        discardChanges(6)
      }
      MAX-ACCESS  read-write
      STATUS      current
      DESCRIPTION
              "When read, this object indicates the state of all the configuration 
               objects in the ioGlobalCfg group (including all sub-groups and
               tables).  
               
               Read values:
               'configUnchanged'
                 Indicates that none of the configuration objects have been 
                 changed since the last submit operation.
               'configChanged' value is read,
                 Indicates that 1 or more of the configuration objects has 
                 changed, and a 'submit_changes' operation is required to commit
                 the values from temporary storage to running config.
                 
               Write values:
               'submitChanges'
                 Causes all configuration objects in the ioGlobalCfg group
                 to be committed from temporary storage to running config.
               'discardChanges'
                 Causes all changes to configuration objects to be discarded
                 from temporary storage (and replaced with values from 
                 running config)."
      ::= { ioGlobalCfg 1 }
      
  ioTemperatureScale OBJECT-TYPE
      SYNTAX      INTEGER {
               celsius(1),
               fahrenheit(2)
      }
      MAX-ACCESS  read-write
      STATUS      current
      DESCRIPTION
              "The temperature scale to be used when displaying 
               thermocouple or RTD values"
      ::= { ioGlobalCfg 2 }
      
  ioFailsafeCfg OBJECT IDENTIFIER ::= { ioGlobalCfg 3 }
  ioFailsafeEnable OBJECT-TYPE
      SYNTAX      OnOffValue
      MAX-ACCESS  read-write
      STATUS      current
      DESCRIPTION
              "Enable/disable I/O failsafe timer"
      ::= { ioFailsafeCfg 1 }
  ioFailsafeTimeout    OBJECT-TYPE
      SYNTAX      Integer32(1..9999)
      MAX-ACCESS  read-write
      STATUS      current
      DESCRIPTION
              "I/O failsafe timeout, in seconds"
      ::= { ioFailsafeCfg 2 }
      
  ioModbusCfg OBJECT IDENTIFIER ::= { ioGlobalCfg 4 }          
  ioModbusEnable OBJECT-TYPE
      SYNTAX      OnOffValue
      MAX-ACCESS  read-write
      STATUS      current
      DESCRIPTION
              "Enable/disable I/O Modbus service"
      ::= { ioModbusCfg 1 }
  ioModbusUid    OBJECT-TYPE
      SYNTAX      Integer32(0..255)
      MAX-ACCESS  read-write
      STATUS      current
      DESCRIPTION
              "I/O Modbus UID"
      ::= { ioModbusCfg 2 }
      
      
  ioUdpCfg OBJECT IDENTIFIER ::= { ioGlobalCfg 5 }
  ioUdpEnable OBJECT-TYPE
      SYNTAX      OnOffValue
      MAX-ACCESS  read-write
      STATUS      current
      DESCRIPTION
              "Enable/disable I/O UDP service"
      ::= { ioUdpCfg 1 }
  
  ioUdpBroadcastInterval    OBJECT-TYPE
      SYNTAX      Integer32(1..9999)
      MAX-ACCESS  read-write
      STATUS      current
      DESCRIPTION
              "I/O UDP broadcast interval, in seconds"
      ::= { ioUdpCfg 2 }
      
-- I/O UDP Table

  ioUdpTable OBJECT-TYPE
      SYNTAX      SEQUENCE OF IoUdpEntry
      MAX-ACCESS  not-accessible
      STATUS      current
      DESCRIPTION
              "Port UDP Table."
      ::= { ioUdpCfg 3 }

  ioUdpEntry OBJECT-TYPE
      SYNTAX      IoUdpEntry
      MAX-ACCESS  not-accessible
      STATUS      current
      DESCRIPTION
              "An entry in the ioUdpEntry, each relating to a port."
      INDEX   { ioUdpEntryIndex }
      ::= { ioUdpTable 1 }

  IoUdpEntry ::=
      SEQUENCE {
        ioUdpEntryIndex            GenericTableIndex,
        ioUdpEntryEnable            OnOffValue,
        ioUdpEntryStartAddress            Ipv4v6Address,
        ioUdpEntryEndAddress            Ipv4v6Address,
        ioUdpEntryPort            Integer32,
        ioUdpEntryTunnelName      DisplayString
        }

  ioUdpEntryIndex OBJECT-TYPE
      SYNTAX      GenericTableIndex
      MAX-ACCESS  not-accessible
      STATUS      current
      DESCRIPTION
              "ioUdpNumber"
      ::= { ioUdpEntry 1 }


  ioUdpEntryEnable  OBJECT-TYPE
      SYNTAX      OnOffValue
      MAX-ACCESS  read-write
      STATUS      current
      DESCRIPTION 
                "Enable/disable this UDP entry"
      ::= { ioUdpEntry 2 }
      
  ioUdpEntryStartAddress OBJECT-TYPE
      SYNTAX      Ipv4v6Address
      MAX-ACCESS  read-write
      STATUS      current
      DESCRIPTION
              "The first host IP address in the range of IP addresses
               (for IPv4 or IPv6) that the Device Server 
               send messages to"
      ::= { ioUdpEntry 3 }

  ioUdpEntryEndAddress OBJECT-TYPE
      SYNTAX      Ipv4v6Address
      MAX-ACCESS  read-write
      STATUS      current
      DESCRIPTION
              "The last host IP address in the range of IP addresses (for
               IPv4, not required for IPv6) that the Device Server will
               send messages to."
      ::= { ioUdpEntry 4 }

  ioUdpEntryPort OBJECT-TYPE
      SYNTAX      Integer32(0..65535)
      MAX-ACCESS  read-write
      STATUS      current
      DESCRIPTION
              "The port that the Device Server will use to 
               relay messages to servers/hosts."
      ::= { ioUdpEntry 5 }
  
  ioUdpEntryTunnelName OBJECT-TYPE
      SYNTAX      DisplayString(SIZE(0..14))
      MAX-ACCESS  read-write
      STATUS      current
      DESCRIPTION
              "The name of the HTTP tunnel associated with this service."
      ::= { ioUdpEntry 6 }
  


  ioTrueportCfg OBJECT IDENTIFIER ::= { ioGlobalCfg 6 }          
  ioTrueportEnable OBJECT-TYPE
      SYNTAX      OnOffValue
      MAX-ACCESS  read-write
      STATUS      current
      DESCRIPTION
          "Enable/disable I/O TruePort service"
      ::= { ioTrueportCfg 1 }
  ioTrueportTcpListenPort    OBJECT-TYPE
      SYNTAX      Integer32(1..65535)
      MAX-ACCESS  read-write
      STATUS      current
      DESCRIPTION
          "I/O TruePort TCP Listening Port"
      ::= { ioTrueportCfg 2 }
      
  ioTrueportSslEnable    OBJECT-TYPE
      SYNTAX      OnOffValue
      MAX-ACCESS  read-write
      STATUS      current
      DESCRIPTION
          "Enable/disable I/O TruePort SSL"
      ::= { ioTrueportCfg 3 }

      
  -- I/O global config ENDS
  
 ioAnalogCfg       OBJECT IDENTIFIER ::= { ioChannelCfg 1 }
 ioDigitalCfg      OBJECT IDENTIFIER ::= { ioChannelCfg 2 }
 ioRelayCfg        OBJECT IDENTIFIER ::= { ioChannelCfg 3 }
 ioLineSignalCfg   OBJECT IDENTIFIER ::= { ioChannelCfg 4 }

-- I/O Analog config BEGINS
  ioAnalogCfgTable OBJECT-TYPE
      SYNTAX      SEQUENCE OF IoAnalogCfgEntry
      MAX-ACCESS  not-accessible
      STATUS      current
      DESCRIPTION
              "ioAnalogCfgTable."
      ::= { ioAnalogCfg 1 }

  ioAnalogCfgEntry OBJECT-TYPE
      SYNTAX      IoAnalogCfgEntry
      MAX-ACCESS  not-accessible
      STATUS      current
      DESCRIPTION
              "An entry in the ioAnalogCfgTable"
      INDEX   { ioAnalogChannelIndex }
      ::= { ioAnalogCfgTable 1 }

  IoAnalogCfgEntry ::= 
      SEQUENCE {
        ioAnalogChannelIndex          GenericTableIndex,
        ioAnalogCfgStatus          ContainerStatus,
        ioAnalogCfgEnable          OnOffValue,
        ioAnalogCfgDescription          DisplayString,
        ioAnalogCfgType          INTEGER,
        ioAnalogCfgRtdRange          INTEGER,
        ioAnalogCfgThermRange          INTEGER,
        ioAnalogCfgCurrentRange          INTEGER,
        ioAnalogCfgVoltageRange          INTEGER,
        ioAnalogCfgAlarmTrigger          INTEGER,
        ioAnalogCfgAlarmClearMode          INTEGER
      }

  ioAnalogChannelIndex OBJECT-TYPE
      SYNTAX      GenericTableIndex
      MAX-ACCESS  not-accessible
      STATUS      current
      DESCRIPTION
              "I/O analog channel resource index"
      ::= { ioAnalogCfgEntry 1 }

  ioAnalogCfgStatus OBJECT-TYPE
      SYNTAX      ContainerStatus
      MAX-ACCESS  read-write
      STATUS      current
      DESCRIPTION
              "NOTE: This object also applies to the corresponding rows
               in ioAnalogAlarmCfgTable.  e.g. If changes are submitted
               to row 1 of this table (i.e. channel 1), then changes will
               also be submitted for all rows in ioAnalogAlarmCfgTable where
               ioAnalogAlarmCfgChannelIndex is equal to 1.
               
               When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioAnalogCfgEntry 2 }

  ioAnalogCfgEnable OBJECT-TYPE
      SYNTAX      OnOffValue
      MAX-ACCESS  read-write
      STATUS      current
      DESCRIPTION
              "Enable/disable this analog I/O resource"
      ::= { ioAnalogCfgEntry 3 }

  ioAnalogCfgDescription OBJECT-TYPE
      SYNTAX      DisplayString(SIZE(0..20))
      MAX-ACCESS  read-write
      STATUS      current
      DESCRIPTION
              "Description for the I/O resource"
      ::= { ioAnalogCfgEntry 4 }

  ioAnalogCfgType OBJECT-TYPE
      SYNTAX      INTEGER {
          none(1),
          rtd(2),
          thermocouple(3),
          current(4),
          voltage(5)
      }
      MAX-ACCESS  read-write
      STATUS      current
      DESCRIPTION
              "Analog I/O resource type.  For current and voltage types, please 
               note that the corresponding hardware jumpers must be set 
               accordingly."
      ::= { ioAnalogCfgEntry 5 }
      
  ioAnalogCfgRtdRange OBJECT-TYPE
      SYNTAX      INTEGER {
          pt100A385RangeMinus50to150(1),
          pt100A385Range0to100(2),
          pt100A385Range0to200(3),
          pt100A385Range0to400(4),
          pt100A385RangeMinus200to200(5),
          pt100A392RangeMinus50to150(6),
          pt100A392Range0to100(7),
          pt100A392Range0to200(8),
          pt100A392Range0to400(9),
          pt100A392RangeMinus200to200(10),
          pt1000A385RangeMinus40to160(11),
          nickelRangeMinus80to100(12),
          nickelRange0to100(13)
          
      }
      MAX-ACCESS  read-write
      STATUS      current
      DESCRIPTION
              "Range for RTD analog I/O"
      ::= { ioAnalogCfgEntry 6 }

  ioAnalogCfgThermRange OBJECT-TYPE
      SYNTAX      INTEGER {
          j(1),
          k(2),
          t(3),
          e(4),
          r(5),
          s(6),
          b(7)
      }
      MAX-ACCESS  read-write
      STATUS      current
      DESCRIPTION
              "Range for thermocouple analog I/O"
      ::= { ioAnalogCfgEntry 7 }

  ioAnalogCfgCurrentRange OBJECT-TYPE
      SYNTAX      INTEGER {
          ampsRange0to20(1),
          ampsRange4to20(2)
      }
      MAX-ACCESS  read-write
      STATUS      current
      DESCRIPTION
              "Range for current-measuring analog I/O"
      ::= { ioAnalogCfgEntry 8 }
      
  ioAnalogCfgVoltageRange OBJECT-TYPE
      SYNTAX      INTEGER {
          voltsRangeMinus10To10(1),
          voltsRangeMinus5To5(2),
          voltsRangeMinus1To1(3),
          millivoltsRangeMinus500to500(4),
          millivoltsRangeMinus150to150(5)
      }
      MAX-ACCESS  read-write
      STATUS      current
      DESCRIPTION
              "Range for voltage-measuring analog I/O"
      ::= { ioAnalogCfgEntry 9 }

  ioAnalogCfgAlarmTrigger OBJECT-TYPE
      SYNTAX      INTEGER {
          disabled(1),
          low(2),
          high(3)
      }
      MAX-ACCESS  read-write
      STATUS      current
      DESCRIPTION
              "Analog I/O alarm trigger type"
      ::= { ioAnalogCfgEntry 10 }

  ioAnalogCfgAlarmClearMode OBJECT-TYPE
      SYNTAX      INTEGER {
          auto(1),
          manual(2)
      }
      MAX-ACCESS  read-write
      STATUS      current
      DESCRIPTION
              "Analog I/O alarm clear mode"
      ::= { ioAnalogCfgEntry 11 }

  ioAnalogAlarmCfgTable OBJECT-TYPE
      SYNTAX      SEQUENCE OF IoAnalogAlarmCfgEntry
      MAX-ACCESS  not-accessible
      STATUS      current
      DESCRIPTION
              "ioAnalogAlarmCfgTable."
      ::= { ioAnalogCfg 2 }

  ioAnalogAlarmCfgEntry OBJECT-TYPE
      SYNTAX      IoAnalogAlarmCfgEntry
      MAX-ACCESS  not-accessible
      STATUS      current
      DESCRIPTION
              "An entry in the ioAnalogAlarmCfgTable"
      INDEX   { ioAnalogAlarmCfgChannelIndex, ioAnalogAlarmCfgEntryIndex }
      ::= { ioAnalogAlarmCfgTable 1 }

  IoAnalogAlarmCfgEntry ::= 
      SEQUENCE 
      {
        ioAnalogAlarmCfgChannelIndex          GenericTableIndex,
        ioAnalogAlarmCfgEntryIndex          GenericTableIndex,
        ioAnalogCfgAlarmEnable          OnOffValue,
        ioAnalogCfgAlarmTriggerLevel          DisplayString,
        ioAnalogCfgAlarmClearLevel          DisplayString,
        ioAnalogCfgAlarmEmail          OnOffValue,
        ioAnalogCfgAlarmSyslog          OnOffValue,
        ioAnalogCfgAlarmSNMP          OnOffValue
      }

  ioAnalogAlarmCfgChannelIndex OBJECT-TYPE
      SYNTAX      GenericTableIndex
      MAX-ACCESS  not-accessible
      STATUS      current
      DESCRIPTION
              "Channel Index"
      ::= { ioAnalogAlarmCfgEntry 1 }

  ioAnalogAlarmCfgEntryIndex OBJECT-TYPE
      SYNTAX      GenericTableIndex
		MAX-ACCESS  not-accessible
      STATUS      current
      DESCRIPTION
              "Entry Index"
      ::= { ioAnalogAlarmCfgEntry 2 }

  ioAnalogCfgAlarmEnable OBJECT-TYPE
      SYNTAX      OnOffValue
      MAX-ACCESS  read-write
      STATUS      current
      DESCRIPTION
              "Enable/disable I/O analog alarm entry"
      ::= { ioAnalogAlarmCfgEntry 3 }
      
  ioAnalogCfgAlarmTriggerLevel OBJECT-TYPE
      SYNTAX      DisplayString
      MAX-ACCESS  read-write
      STATUS      current
      DESCRIPTION
              "Trigger level for I/O analog alarm (floating point value)"
      ::= { ioAnalogAlarmCfgEntry 4 }
      
  ioAnalogCfgAlarmClearLevel OBJECT-TYPE
      SYNTAX      DisplayString
      MAX-ACCESS  read-write
      STATUS      current
      DESCRIPTION
              "Clear level for non-latching I/O analog alarm (floating point 
               value)"
      ::= { ioAnalogAlarmCfgEntry 5 }
      
  ioAnalogCfgAlarmEmail OBJECT-TYPE
      SYNTAX      OnOffValue
      MAX-ACCESS  read-write
      STATUS      current
      DESCRIPTION
              "Enable/disable email notification on triggered analog alarm"
      ::= { ioAnalogAlarmCfgEntry 6 }
      
  ioAnalogCfgAlarmSyslog OBJECT-TYPE
      SYNTAX      OnOffValue
      MAX-ACCESS  read-write
      STATUS      current
      DESCRIPTION
              "Enable/disable syslog notification on triggered analog alarm"
      ::= { ioAnalogAlarmCfgEntry 7 }
      
  ioAnalogCfgAlarmSNMP OBJECT-TYPE
      SYNTAX      OnOffValue
      MAX-ACCESS  read-write
      STATUS      current
      DESCRIPTION
              "Enable/disable SNMP trap notification on triggered analog alarm"
      ::= { ioAnalogAlarmCfgEntry 8 }
      
  -- I/O Analog config ENDS

  -- I/O Digital config BEGINS
  ioDigitalCfgTable OBJECT-TYPE
      SYNTAX      SEQUENCE OF IoDigitalCfgEntry
      MAX-ACCESS  not-accessible
      STATUS      current
      DESCRIPTION
              "ioDigitalCfgTable."
      ::= { ioDigitalCfg 1 }

  ioDigitalCfgEntry OBJECT-TYPE
      SYNTAX      IoDigitalCfgEntry
      MAX-ACCESS  not-accessible
      STATUS      current
      DESCRIPTION
              "An entry in the ioDigitalCfgTable"
      INDEX   { ioDigitalChannelIndex }
      ::= { ioDigitalCfgTable 1 }

  IoDigitalCfgEntry ::= 
      SEQUENCE {
        ioDigitalChannelIndex          GenericTableIndex,
        ioDigitalCfgStatus          ContainerStatus,
        ioDigitalCfgResourceType          INTEGER,
        ioDigitalCfgEnable          OnOffValue,
        ioDigitalCfgDescription          DisplayString,
        ioDigitalInputCfgLatch          INTEGER,
        ioDigitalInputCfgInvertSignal          OnOffValue,
        ioDigitalInputCfgAlarmTrigger          INTEGER,
        ioDigitalInputCfgAlarmClear          INTEGER,
        ioDigitalInputCfgAlarmEmail          OnOffValue,
        ioDigitalInputCfgAlarmSyslog          OnOffValue,
        ioDigitalInputCfgAlarmSNMP          OnOffValue,
        ioDigitalOutputCfgType          INTEGER,
        ioDigitalOutputCfgMode          INTEGER,
        ioDigitalOutputCfgPulseMode          INTEGER,
        ioDigitalOutputCfgPulseCount          Integer32,
        ioDigitalOutputCfgInactiveSignalWidth          Integer32,
        ioDigitalOutputCfgActiveSignalWidth          Integer32,
        ioDigitalOutputCfgDelay          Integer32,
        ioDigitalOutputCfgFailsafe          INTEGER
      }

  ioDigitalChannelIndex OBJECT-TYPE
      SYNTAX      GenericTableIndex
      MAX-ACCESS  not-accessible
      STATUS      current
      DESCRIPTION
              "I/O digital channel resource index"
      ::= { ioDigitalCfgEntry 1 }

  ioDigitalCfgStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioDigitalCfgEntry 2 }

  ioDigitalCfgResourceType OBJECT-TYPE
      SYNTAX      INTEGER {
         input(2),   
         output(3)
      }
      MAX-ACCESS  read-write
      STATUS      current
      DESCRIPTION
              "Set your digital I/O resource type to Input or Output
               using this object.  Please note that the corresponding 
               hardware jumpers must be set accordingly."
      ::= { ioDigitalCfgEntry 3 }
      
  ioDigitalCfgEnable OBJECT-TYPE
      SYNTAX      OnOffValue
      MAX-ACCESS  read-write
      STATUS      current
      DESCRIPTION
              "Enable/disable this digital I/O channel"
      ::= { ioDigitalCfgEntry 4 }

  ioDigitalCfgDescription OBJECT-TYPE
      SYNTAX      DisplayString(SIZE(0..20))
      MAX-ACCESS  read-write
      STATUS      current
      DESCRIPTION
              "Description for this digital I/O "
      ::= { ioDigitalCfgEntry 5 }

  ioDigitalInputCfgLatch OBJECT-TYPE
      SYNTAX      INTEGER {
         disabled(1),
         inactiveToActive(2),
         activeToInactive(3)
      }
      MAX-ACCESS  read-write
      STATUS      current
      DESCRIPTION
              "Digital Input: Latch type"
      ::= { ioDigitalCfgEntry 6 }

  ioDigitalInputCfgInvertSignal OBJECT-TYPE
      SYNTAX      OnOffValue
      MAX-ACCESS  read-write
      STATUS      current
      DESCRIPTION
              "Digital Input: Enable/disable signal inversion"
      ::= { ioDigitalCfgEntry 7 }

  ioDigitalInputCfgAlarmTrigger OBJECT-TYPE
      SYNTAX      INTEGER {
        disabled(1),
        low(2),
        high(3)
      }
      MAX-ACCESS  read-write
      STATUS      current
      DESCRIPTION
              "Digital Input: Alarm trigger type"
      ::= { ioDigitalCfgEntry 8 }
      
  ioDigitalInputCfgAlarmClear OBJECT-TYPE
      SYNTAX      INTEGER {
        auto(1),
        manual(2)
      }
      MAX-ACCESS  read-write
      STATUS      current
      DESCRIPTION
              "Digital Input: Clear alarm - manual/automatic"
      ::= { ioDigitalCfgEntry 9 }
      
  ioDigitalInputCfgAlarmEmail OBJECT-TYPE
      SYNTAX      OnOffValue
      MAX-ACCESS  read-write
      STATUS      current
      DESCRIPTION
              "Digital Input: Enable/disable email alert on triggered alarm"
      ::= { ioDigitalCfgEntry 10 }
      
  ioDigitalInputCfgAlarmSyslog OBJECT-TYPE
      SYNTAX      OnOffValue
      MAX-ACCESS  read-write
      STATUS      current
      DESCRIPTION
              "Digital Input: Enable/disable syslog alert on triggered alarm"
      ::= { ioDigitalCfgEntry 11 }
      
  ioDigitalInputCfgAlarmSNMP OBJECT-TYPE
      SYNTAX      OnOffValue
      MAX-ACCESS  read-write
      STATUS      current
      DESCRIPTION
              "Digital Input: Enable/disable SNMP trap on triggered alarm"
      ::= { ioDigitalCfgEntry 12 }
      
      
  ioDigitalOutputCfgType OBJECT-TYPE
      SYNTAX      INTEGER {
         sink(1),
         source(2),
         sinkAndSource(3)
      }
      MAX-ACCESS  read-write
      STATUS      current
      DESCRIPTION
              "Digital Output: Output type"
      ::= { ioDigitalCfgEntry 13 }
      
  ioDigitalOutputCfgMode OBJECT-TYPE
      SYNTAX      INTEGER {
         manual(1),
         pulse(2),
         inactiveToActiveDelay(3),
         activeToInactiveDelay(4)
      }
      MAX-ACCESS  read-write
      STATUS      current
      DESCRIPTION
              "Digital Output: Output mode"
      ::= { ioDigitalCfgEntry 14 }

  ioDigitalOutputCfgPulseMode OBJECT-TYPE
      SYNTAX      INTEGER {
         continuous(1),
         counted(2)
      }
      MAX-ACCESS  read-write
      STATUS      current
      DESCRIPTION
              "Digital Output: Pulse mode (counted or continuous)"
      ::= { ioDigitalCfgEntry 15 }
      

  ioDigitalOutputCfgPulseCount OBJECT-TYPE
      SYNTAX      Integer32(1..9999)
      MAX-ACCESS  read-write
      STATUS      current
      DESCRIPTION
              "Digital Output: Pulse count (only applies to counted pulse mode)"
      ::= { ioDigitalCfgEntry 16 }
      
  ioDigitalOutputCfgInactiveSignalWidth OBJECT-TYPE
      SYNTAX      Integer32(1..9999)
      MAX-ACCESS  read-write
      STATUS      current
      DESCRIPTION
              "Digital Output: Inactive signal width, in 100 ms units (only applies 
               to pulse mode)"
      ::= { ioDigitalCfgEntry 17 }
      
  ioDigitalOutputCfgActiveSignalWidth OBJECT-TYPE
      SYNTAX      Integer32(1..9999)
      MAX-ACCESS  read-write
      STATUS      current
      DESCRIPTION
              "Digital Output: Active signal width, in 100 ms units (only applies 
               to pulse mode)"
      ::= { ioDigitalCfgEntry 18 }
      
  ioDigitalOutputCfgDelay OBJECT-TYPE
      SYNTAX      Integer32(1..9999)
      MAX-ACCESS  read-write
      STATUS      current
      DESCRIPTION
              "Digital Output: Delay time, in 100 ms units (only applies to 
               delay mode)"
      ::= { ioDigitalCfgEntry 19 }
      
  ioDigitalOutputCfgFailsafe OBJECT-TYPE
      SYNTAX      INTEGER {
          none(1),
          activateOutput(2),
          deactivateOutput(3)
      }
      MAX-ACCESS  read-write
      STATUS      current
      DESCRIPTION
              "Digital Output: Failsafe action - choose the action that 
               will take place when the failsafe timer expires"
      ::= { ioDigitalCfgEntry 20 }
      
-- I/O Digial Extension code start 
  ioDigitalExtensionCfgTable OBJECT-TYPE
      SYNTAX      SEQUENCE OF IoDigitalExtensionCfgEntry
      MAX-ACCESS  not-accessible
      STATUS      current
      DESCRIPTION
              "I/O Digial Extention Table."
      ::= { ioDigitalCfg 2 }

  ioDigitalExtensionCfgEntry OBJECT-TYPE
      SYNTAX      IoDigitalExtensionCfgEntry
      MAX-ACCESS  not-accessible
      STATUS      current
      DESCRIPTION
              "An entry in the ioDigitalExtensionCfgTable"
      INDEX   { ioDigitalExtCfgChanIndex }
      ::= { ioDigitalExtensionCfgTable 1 }

  IoDigitalExtensionCfgEntry ::=
      SEQUENCE {
        ioDigitalExtCfgChanIndex          GenericTableIndex,
        ioDigitalExtCfgStatus          ContainerStatus,		
        ioDigitalExtCfgEnable          OnOffValue,
        ioDigitalExtCfgConnMethod            INTEGER,
        ioDigitalExtCfgHost          DisplayString,
        ioDigitalExtCfgPort            Integer32,
        ioDigitalExtCfgLinkChannel          DisplayString,
        ioDigitalExtCfgKeepalive          OnOffValue,
        ioDigitalExtCfgMultiHost          OnOffValue,
        ioDigitalExtCfgTunnelName    DisplayString
        }

  ioDigitalExtCfgChanIndex OBJECT-TYPE
      SYNTAX      GenericTableIndex
      MAX-ACCESS  not-accessible
      STATUS      current
      DESCRIPTION
              "I/O resource index"
      ::= { ioDigitalExtensionCfgEntry 1}
  
  ioDigitalExtCfgStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioDigitalExtensionCfgEntry 2 }
	  
  ioDigitalExtCfgEnable OBJECT-TYPE
      SYNTAX      OnOffValue
      MAX-ACCESS  read-write
      STATUS      current
      DESCRIPTION
              "Enable/disable this digital  I/O Extension"
      ::= { ioDigitalExtensionCfgEntry 3 }
	  
  ioDigitalExtCfgConnMethod OBJECT-TYPE
      SYNTAX      INTEGER {
        listen(0),
        connect(1),
        local(2)
      }
      MAX-ACCESS  read-write
      STATUS      current
      DESCRIPTION
              "Defines the type of connection being established
			   Listen for connection, Connect to Host, or Local"
      ::= { ioDigitalExtensionCfgEntry 4}
	  
  ioDigitalExtCfgHost OBJECT-TYPE
      SYNTAX      DisplayString(SIZE(0..14))
      MAX-ACCESS  read-write
      STATUS      current
      DESCRIPTION
              "The name of the target host."
      ::= { ioDigitalExtensionCfgEntry 5}
	  
  ioDigitalExtCfgPort OBJECT-TYPE
      SYNTAX      Integer32(0..65535)
      MAX-ACCESS  read-write
      STATUS      current
      DESCRIPTION
              "The port number the target host is listening on for incoming/outgoing connections."
      ::= { ioDigitalExtensionCfgEntry 6}
	  
  ioDigitalExtCfgLinkChannel OBJECT-TYPE
      SYNTAX      DisplayString(SIZE(0..10))
      MAX-ACCESS  read-write
      STATUS      current
      DESCRIPTION
              "The Link Channel that device would make a connection with.  The link channel is only valid for Local 
			  connection.  The channel must be digital input"
      ::= { ioDigitalExtensionCfgEntry 7 }
	  
  ioDigitalExtCfgKeepalive OBJECT-TYPE
      SYNTAX      OnOffValue
      MAX-ACCESS  read-write
      STATUS      current
      DESCRIPTION
              "Enables a per-connection TCP keepalive feature; after approximately
               3 minutes of network connection idle time, the connection will send
               a gratuitous ACK to the network peer, either ensuring the connection 
               stays active OR causing a dropped connection condition to be recognized
               by the reverse raw service.
               Applications using this feature need to be aware that there might be 
               some considerable delay between a network disconnection and the port 
               being available for the next connection attempt; this is to allow any 
               data sent on prior connections to be transmitted out of the serial 
               port buffer. Application network retry logic needs to accommodate this feature."
      ::= { ioDigitalExtensionCfgEntry 8}
  
  ioDigitalExtCfgMultiHost OBJECT-TYPE
      SYNTAX      OnOffValue
      MAX-ACCESS  read-write
      STATUS      current
      DESCRIPTION
              "Allows user to configure the multihost for client/server initiated connections"
      ::= { ioDigitalExtensionCfgEntry 9}
      
  ioDigitalExtCfgTunnelName OBJECT-TYPE
      SYNTAX      DisplayString(SIZE(0..14))
      MAX-ACCESS  read-write
      STATUS      current
      DESCRIPTION
              "The name of the HTTP tunnel associated with the Rlogin service."
      ::= { ioDigitalExtensionCfgEntry 10 }
  
  
-- I/O Digialextension code ends

-- I/O Digital Multihost Table
  ioDigitalMultihostTable OBJECT-TYPE
      SYNTAX      SEQUENCE OF IoDigitalMultihostEntry
      MAX-ACCESS  not-accessible
      STATUS      current
      DESCRIPTION
              "I/O Digial Multihost Table."
      ::= { ioDigitalCfg 3 }

  ioDigitalMultihostEntry OBJECT-TYPE
      SYNTAX      IoDigitalMultihostEntry
      MAX-ACCESS  not-accessible
      STATUS      current
      DESCRIPTION
              "An entry in the ioDigitalMultihostEntry, each relating to digital io channel."
      INDEX   { ioDigitalMultihostIndex }
      ::= { ioDigitalMultihostTable 1 }

  IoDigitalMultihostEntry ::=
      SEQUENCE {
        ioDigitalMultihostIndex            GenericTableIndex,
        ioDigitalMultihostStatus            ContainerStatus,
        ioDigitalMultihostMode            INTEGER
        
        }

  ioDigitalMultihostIndex OBJECT-TYPE
      SYNTAX      GenericTableIndex
      MAX-ACCESS  not-accessible
      STATUS      current
      DESCRIPTION
              "ioDigitalMultihostIndex"
      ::= { ioDigitalMultihostEntry 1}
   
  ioDigitalMultihostStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioDigitalMultihostEntry 2}

  ioDigitalMultihostMode OBJECT-TYPE
        SYNTAX      INTEGER {
        all(1),
        backup(2)
      }
      MAX-ACCESS  read-write
      STATUS      current
      DESCRIPTION
              "Set multihost operation mode.all:for muliple host list mode. backup: for primary-backup mode"
      ::= { ioDigitalMultihostEntry 4}

-- I/O Digital multihost outbound Table

  ioDigitalMultihostOutboundTable OBJECT-TYPE
      SYNTAX      SEQUENCE OF IoDigitalMultihostOutboundEntry
      MAX-ACCESS  not-accessible
      STATUS      current
      DESCRIPTION
              "Multihost outbound table."
      ::= {ioDigitalCfg 4}
      
  ioDigitalMultihostOutboundEntry OBJECT-TYPE
      SYNTAX      IoDigitalMultihostOutboundEntry
      MAX-ACCESS  not-accessible
      STATUS      current
      DESCRIPTION
              "An entry in the ioDigitalMultihostOutboundTable."
      INDEX   {ioDigitalMultihostChanIndex, ioDigitalMultihostOutboundIndex }
      ::= { ioDigitalMultihostOutboundTable 1 }

  IoDigitalMultihostOutboundEntry ::=
      SEQUENCE {
  ioDigitalMultihostChanIndex        GenericTableIndex,
  ioDigitalMultihostOutboundIndex        GenericTableIndex,
  ioDigitalMultihostOutboundStatus        ContainerStatus,
  ioDigitalMultihostOutboundHostID        DisplayString,
  ioDigitalMultihostOutboundTcpPort        Integer32,
  ioDigitalMultihostOutboundTunnel        DisplayString
      }

   ioDigitalMultihostChanIndex OBJECT-TYPE
      SYNTAX      GenericTableIndex
      MAX-ACCESS  not-accessible
      STATUS      current
      DESCRIPTION
              "Channel Index"
      ::= { ioDigitalMultihostOutboundEntry 1 }

  ioDigitalMultihostOutboundIndex OBJECT-TYPE
      SYNTAX      GenericTableIndex
      MAX-ACCESS  not-accessible
      STATUS      current
      DESCRIPTION
              "The outbound entry number"
      ::= { ioDigitalMultihostOutboundEntry 2 }

  ioDigitalMultihostOutboundStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioDigitalMultihostOutboundEntry 3 }


  ioDigitalMultihostOutboundHostID OBJECT-TYPE
      SYNTAX      DisplayString (SIZE(0..14))
      MAX-ACCESS  read-write
      STATUS      current
      DESCRIPTION
              "The host name."
      ::= { ioDigitalMultihostOutboundEntry 4 }

  ioDigitalMultihostOutboundTcpPort OBJECT-TYPE
      SYNTAX      Integer32(0..65535)
      MAX-ACCESS  read-write
      STATUS      current
      DESCRIPTION
              "The host TCP port."
      ::= { ioDigitalMultihostOutboundEntry 5 }

  ioDigitalMultihostOutboundTunnel OBJECT-TYPE
      SYNTAX      DisplayString (SIZE(0..14))
      MAX-ACCESS  read-write
      STATUS      current
      DESCRIPTION
              "The HTTP tunnel associated with this host."
      ::= { ioDigitalMultihostOutboundEntry 6 }
  
	  
-- I/O Digital multihost outbound Table ends

-- IO Digial SSL Info
  ioDigitalSSLTable OBJECT-TYPE
      SYNTAX      SEQUENCE OF IoDigitalSSLEntry
      MAX-ACCESS  not-accessible
      STATUS      current
      DESCRIPTION
              "io SSL Table."
      ::= { ioDigitalCfg 5 }

  ioDigitalSSLEntry OBJECT-TYPE
      SYNTAX      IoDigitalSSLEntry
      MAX-ACCESS  not-accessible
      STATUS      current
      DESCRIPTION
              "An entry in the ioDigitalSSLEntry, each relating to a io."
      INDEX   { ioDigitalSSLIndex }
      ::= { ioDigitalSSLTable 1 }

  IoDigitalSSLEntry ::=
     SEQUENCE {
        ioDigitalSSLIndex        GenericTableIndex,
        ioDigitalSSLStatus       ContainerStatus,
        ioDigitalSSLEnabled        OnOffValue,
        ioDigitalSSLuseServer        OnOffValue,
        ioDigitalSSLVersion        INTEGER,
        ioDigitalSSLType        INTEGER,
        ioDigitalSSLVerifyPeerCertificate        OnOffValue,
        ioDigitalSSLCountry        DisplayString,
        ioDigitalSSLStateProv        DisplayString,
        ioDigitalSSLLocality        DisplayString,
        ioDigitalSSLOrganisation        DisplayString,
        ioDigitalSSLOrganisationUnit        DisplayString,
        ioDigitalSSLCommonName        DisplayString,
        ioDigitalSSLEmail        DisplayString
     }

  ioDigitalSSLIndex OBJECT-TYPE
      SYNTAX      GenericTableIndex
      MAX-ACCESS  not-accessible
      STATUS      current
      DESCRIPTION
              "io Digital SSL Index"
      ::= { ioDigitalSSLEntry 1}

  ioDigitalSSLStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {ioDigitalSSLEntry 2}

  ioDigitalSSLEnabled  OBJECT-TYPE
      SYNTAX   OnOffValue
      MAX-ACCESS    read-write
      STATUS        current
      DESCRIPTION
                "Enables/disables SSL."
      ::= {ioDigitalSSLEntry 3}

  ioDigitalSSLuseServer  OBJECT-TYPE
      SYNTAX   OnOffValue
      MAX-ACCESS    read-write
      STATUS        current
      DESCRIPTION
                "Uses the SSL/TLS server configuration for the line."
      ::= {ioDigitalSSLEntry 4}

  ioDigitalSSLVersion  OBJECT-TYPE
      SYNTAX      INTEGER {
        any(1),
        tlsv1(2),
        sslv3(3)
      }
      MAX-ACCESS    read-write
      STATUS        current
      DESCRIPTION
                "Specify whether you want to use:
                 Any-The Device Server will try a TLSv1 connection first.
                     If that fails, it will try an SSLv3 connection. 
                     If that fails, it will try an SSLv2 connection.
                 TLSv1-The connection will use only TLSv1.
                 SSLv3-The connection will use only SSLv3.
                 The default is Any."
      ::= {ioDigitalSSLEntry 5}

  ioDigitalSSLType    OBJECT-TYPE
      SYNTAX      INTEGER {
        client(1),
        server(2)
      }
      MAX-ACCESS    read-write
      STATUS        current
      DESCRIPTION
                "Specify whether the Device Server will act as an 
                 SSL/TLS client or server. The default is Client."
      ::= {ioDigitalSSLEntry 6}

  ioDigitalSSLVerifyPeerCertificate  OBJECT-TYPE
      SYNTAX   OnOffValue
      MAX-ACCESS    read-write
      STATUS        current
      DESCRIPTION
                "Enable this option when you want the Validation Criteria
                 to match the Peer Certificate for authentication to pass.
                 If you enable this option, you need to download an  
                 SSL/TLS certificate authority (CA) list file to the 
                 Device Server. Any values that are entered in the validation
                 criteria must match the peer certificate for an SSL connection;
                 any fields left blank will not be validated against the peer 
                 certificate."
      ::= {ioDigitalSSLEntry 7}

  ioDigitalSSLCountry    OBJECT-TYPE
      SYNTAX      DisplayString(SIZE(0..2))
      MAX-ACCESS    read-write
      STATUS        current
      DESCRIPTION
                "A two character country code; for example, US."
      ::= {ioDigitalSSLEntry 8}

  ioDigitalSSLStateProv    OBJECT-TYPE
      SYNTAX      DisplayString(SIZE(0..128))
      MAX-ACCESS    read-write
      STATUS        current
      DESCRIPTION
                "Up to a 128 character entry for the state/province;
                 for example, IL."
      ::= {ioDigitalSSLEntry 9}

  ioDigitalSSLLocality    OBJECT-TYPE
      SYNTAX      DisplayString(SIZE(0..128))
      MAX-ACCESS    read-write
      STATUS        current
      DESCRIPTION
                "Up to a 128 character entry for the location; 
                 for example, a city."
      ::= {ioDigitalSSLEntry 10}

  ioDigitalSSLOrganisation    OBJECT-TYPE
      SYNTAX      DisplayString(SIZE(0..64))
      MAX-ACCESS    read-write
      STATUS        current
      DESCRIPTION
                "Up to a 64 character entry for the organization; 
                 for example, Accounting."
      ::= {ioDigitalSSLEntry 11}

  ioDigitalSSLOrganisationUnit    OBJECT-TYPE
      SYNTAX      DisplayString(SIZE(0..64))
      MAX-ACCESS    read-write
      STATUS        current
      DESCRIPTION
                "Up to a 64 character entry for the unit in the 
                 organization; for example, Payroll."
      ::= {ioDigitalSSLEntry 12}

  ioDigitalSSLCommonName    OBJECT-TYPE
      SYNTAX      DisplayString(SIZE(0..64))
      MAX-ACCESS    read-write
      STATUS        current
      DESCRIPTION
                "Up to a 64 character entry for common name; for example,
                 the host name or fully qualified domain name."
      ::= {ioDigitalSSLEntry 13}

  ioDigitalSSLEmail    OBJECT-TYPE
      SYNTAX      DisplayString(SIZE(0..128))
      MAX-ACCESS    read-write
      STATUS        current
      DESCRIPTION
                "Up to a 64 character entry for an email address; 
                 for example, acct@anycompany.com."
      ::= {ioDigitalSSLEntry 14}

-- io SSL Server Cipher Table

  ioDigitalSSLCipherTable OBJECT-TYPE
      SYNTAX      SEQUENCE OF IoDigitalSSLCipherEntry
      MAX-ACCESS  not-accessible
      STATUS      current
      DESCRIPTION
              "Digital SSL Cipher."
      ::= {ioDigitalCfg 6}

  ioDigitalSSLCipherEntry OBJECT-TYPE
      SYNTAX      IoDigitalSSLCipherEntry
      MAX-ACCESS  not-accessible
      STATUS      current
      DESCRIPTION
              "An entry in the sslCipherTable, each relating to a cipher entry."
      INDEX   { ioDigitalSSLChanIndex, ioDigitalSSLCipherIndex }
      ::= { ioDigitalSSLCipherTable 1 }

  IoDigitalSSLCipherEntry ::=
      SEQUENCE {
  ioDigitalSSLChanIndex        GenericTableIndex,
  ioDigitalSSLCipherIndex       Integer32,
  ioDigitalSSLCipherStatus        ContainerStatus,
  ioDigitalSSLCipherEncryption        INTEGER,
  ioDigitalSSLCipherKeySizeMin        INTEGER,
  ioDigitalSSLCipherKeySizeMax        INTEGER,
  ioDigitalSSLCipherKeyExchange        INTEGER,
  ioDigitalSSLCipherHMAC        INTEGER
      }

  ioDigitalSSLChanIndex OBJECT-TYPE
      SYNTAX      GenericTableIndex
      MAX-ACCESS  not-accessible
      STATUS      current
      DESCRIPTION
              "The io number"
      ::= { ioDigitalSSLCipherEntry 1 }
   
  ioDigitalSSLCipherIndex OBJECT-TYPE
      SYNTAX      Integer32(1..5)
      MAX-ACCESS  not-accessible
      STATUS      current
      DESCRIPTION
              "The cipher priority. 1- highest 5 - lowest."
      ::= { ioDigitalSSLCipherEntry 2 }

  ioDigitalSSLCipherStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioDigitalSSLCipherEntry 3 }

  ioDigitalSSLCipherEncryption OBJECT-TYPE
      SYNTAX      INTEGER {
        none(1),
        any(2),
        aes(3),
        tripledes(4),
        des(5),
        arctwo(6),
        arcfour(7)
      }
      MAX-ACCESS  read-write
      STATUS      current
      DESCRIPTION
              "SSL Encryption. None is not allowed for priority 1.
               Any will use the first encryption format that can be 
               negotiated. The default is any."
      ::= { ioDigitalSSLCipherEntry 4 }

  ioDigitalSSLCipherKeySizeMin OBJECT-TYPE
      SYNTAX      INTEGER {
        min40(1),
        min56(2),
        min64(3),
        min128(4),
        min168(5),
        min256(6)
      }
      MAX-ACCESS  read-write
      STATUS      current
      DESCRIPTION
              "The minimum key size value that will be used for 
               the specified encryption type. The default is 40."
      ::= { ioDigitalSSLCipherEntry 5 }

  ioDigitalSSLCipherKeySizeMax OBJECT-TYPE
      SYNTAX      INTEGER {
        max40(1),
        max56(2),
        max64(3),
        max128(4),
        max168(5),
        max256(6)
      }
      MAX-ACCESS  read-write
      STATUS      current
      DESCRIPTION
              "The maximum key size value that will be used for the
               specified encryption type. The default is 256."
      ::= { ioDigitalSSLCipherEntry 6 }

  ioDigitalSSLCipherKeyExchange OBJECT-TYPE
      SYNTAX      INTEGER {
        any(1),
        rsa(2),
        edhrsa(3),
        edhdss(4),
        adh(5)
      }
      MAX-ACCESS  read-write
      STATUS      current
      DESCRIPTION
              "The type of key to exchange for the encryption format:
               Any-Any key exchange that is valid is used (this does 
                   not, however, include ADH keys).
               RSA-This is an RSA key exchange using an RSA key and 
                   certificate.
               EDHRSA-This is an EDH key exchange using an RSA key 
                   and certificate.
               EDHDSS-This is an EDH key exchange using a DSA key
                   and certificate.
               ADH-This is an anonymous key exchange which does not 
                   require a private key or certificate. Choose this 
                   key if you do not want to authenticate the peer device, 
                   but you want the data encrypted on the SSL/TLS connection.
               The default is Any."
      ::= { ioDigitalSSLCipherEntry 7 }

  ioDigitalSSLCipherHMAC OBJECT-TYPE
      SYNTAX      INTEGER {
        any(1),
        sha(2),
        md5(3)
      }
      MAX-ACCESS  read-write
      STATUS      current
      DESCRIPTION
              "Select the key-hashing for message authentication method 
               for your encryption type: Any, MD5, or SHA1.
               The default is Any."
      ::= { ioDigitalSSLCipherEntry 8 }
      

  -- IO Digital SSL Server Cipher Table ENDS

  -- I/O Digital Cfg ENDS

  
  -- I/O Relay config BEGINS
  ioRelayCfgTable OBJECT-TYPE
      SYNTAX      SEQUENCE OF IoRelayCfgEntry
      MAX-ACCESS  not-accessible
      STATUS      current
      DESCRIPTION
              "ioRelayCfgTable."
      ::= { ioRelayCfg 1 }

  ioRelayCfgEntry OBJECT-TYPE
      SYNTAX      IoRelayCfgEntry
      MAX-ACCESS  not-accessible
      STATUS      current
      DESCRIPTION
              "An entry in the ioRelayCfgTable"
      INDEX   { ioRelayChannelIndex }
      ::= { ioRelayCfgTable 1 }

  IoRelayCfgEntry ::= 
      SEQUENCE 
      {
        ioRelayChannelIndex          GenericTableIndex,
        ioRelayCfgStatus          ContainerStatus,
        ioRelayCfgEnable          OnOffValue,
        ioRelayCfgDescription          DisplayString,
        ioRelayCfgMode          INTEGER,
        ioRelayCfgPulseMode          INTEGER,
        ioRelayCfgPulseCount          Integer32,
        ioRelayCfgInactiveSignalWidth          Integer32,
        ioRelayCfgActiveSignalWidth          Integer32,
        ioRelayCfgDelay          Integer32,
        ioRelayCfgFailsafe          INTEGER
      }

  ioRelayChannelIndex OBJECT-TYPE
      SYNTAX       GenericTableIndex
      MAX-ACCESS  not-accessible
      STATUS      current
      DESCRIPTION
              "I/O relay channel resource index"
      ::= { ioRelayCfgEntry 1 }

  ioRelayCfgStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioRelayCfgEntry 2 }

  ioRelayCfgEnable OBJECT-TYPE
      SYNTAX      OnOffValue
      MAX-ACCESS  read-write
      STATUS      current
      DESCRIPTION
              "Enable/disable this Relay I/O channel"
      ::= { ioRelayCfgEntry 3 }

  ioRelayCfgDescription OBJECT-TYPE
      SYNTAX      DisplayString(SIZE(0..20))
      MAX-ACCESS  read-write
      STATUS      current
      DESCRIPTION
              "Description for this relay"
      ::= { ioRelayCfgEntry 4 }

  ioRelayCfgMode OBJECT-TYPE
      SYNTAX      INTEGER {
         manual(1),
         pulse(2),
         inactiveToActiveDelay(3),
         activeToInactiveDelay(4)
      }
      MAX-ACCESS  read-write
      STATUS      current
      DESCRIPTION
              "Relay output mode"
      ::= { ioRelayCfgEntry 5 }

  ioRelayCfgPulseMode OBJECT-TYPE
      SYNTAX      INTEGER {
         continuous(1),
         counted(2)
      }
      MAX-ACCESS  read-write
      STATUS      current
      DESCRIPTION
              "Relay pulse mode (only applies when output mode is set to 'pulse'"
      ::= { ioRelayCfgEntry 6 }
      

  ioRelayCfgPulseCount OBJECT-TYPE
      SYNTAX      Integer32(1..9999)
      MAX-ACCESS  read-write
      STATUS      current
      DESCRIPTION
              "Relay pulse count; only applies for counted pulse mode"
      ::= { ioRelayCfgEntry 7 }
      
  ioRelayCfgInactiveSignalWidth OBJECT-TYPE
      SYNTAX      Integer32(1..9999)
      MAX-ACCESS  read-write
      STATUS      current
      DESCRIPTION
              "Relay inactive signal width in 100 ms units; only applies to pulse mode"
      ::= { ioRelayCfgEntry 8 }
      
  ioRelayCfgActiveSignalWidth OBJECT-TYPE
      SYNTAX      Integer32(1..9999)
      MAX-ACCESS  read-write
      STATUS      current
      DESCRIPTION
              "Relay active signal width in 100 ms units; only applies to pulse mode"
      ::= { ioRelayCfgEntry 9 }
      
  ioRelayCfgDelay OBJECT-TYPE
      SYNTAX      Integer32(1..9999)
      MAX-ACCESS  read-write
      STATUS      current
      DESCRIPTION
              "Relay pulse delay, in 100 ms units; only applies to delay mode"
      ::= { ioRelayCfgEntry 10 }
      
  ioRelayCfgFailsafe OBJECT-TYPE
      SYNTAX      INTEGER {
          none(1),
          activateOutput(2),
          deactivateOutput(3)
      }
      MAX-ACCESS  read-write
      STATUS      current
      DESCRIPTION
              "Action to take when the failsafe timer expires"
      ::= { ioRelayCfgEntry 11 }
	  
-- Io extension Relay code start	  
  ioRelayExtensionCfgTable OBJECT-TYPE
      SYNTAX      SEQUENCE OF IoRelayExtensionCfgEntry
      MAX-ACCESS  not-accessible
      STATUS      current
      DESCRIPTION
              "ioRelayExtensionCfgTable"
      ::= { ioRelayCfg 2 }

  ioRelayExtensionCfgEntry OBJECT-TYPE
      SYNTAX      IoRelayExtensionCfgEntry
      MAX-ACCESS  not-accessible
      STATUS      current
      DESCRIPTION
              "An entry in the ioReleayExtensionCfgTable"
      INDEX   { ioRelayExtCfgChanIndex }
      ::= { ioRelayExtensionCfgTable 1 }

  IoRelayExtensionCfgEntry ::=
      SEQUENCE {
        ioRelayExtCfgChanIndex            GenericTableIndex,
        ioRelayExtCfgStatus			ContainerStatus,		
        ioRelayExtCfgEnable          OnOffValue,
        ioRelayExtCfgConnMethod            INTEGER,
        ioRelayExtCfgHost			DisplayString,
        ioRelayExtCfgPort            Integer32,
        ioRelayExtCfgLinkChannel			DisplayString,
        ioRelayExtCfgKeepalive          OnOffValue,
        ioRelayExtCfgMultiHost          OnOffValue,
        ioRelayExtCfgTunnelName         DisplayString
      }

  ioRelayExtCfgChanIndex OBJECT-TYPE
      SYNTAX      GenericTableIndex
      MAX-ACCESS  not-accessible
      STATUS      current
      DESCRIPTION
              "I/O Relay channel resource index"
      ::= { ioRelayExtensionCfgEntry 1}
   
  ioRelayExtCfgStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioRelayExtensionCfgEntry 2 }
	  
  ioRelayExtCfgEnable OBJECT-TYPE
      SYNTAX      OnOffValue
      MAX-ACCESS  read-write
      STATUS      current
      DESCRIPTION
              "Enable/disable this digital  I/O Extension"
      ::= { ioRelayExtensionCfgEntry 3 }
	  
  ioRelayExtCfgConnMethod OBJECT-TYPE
      SYNTAX      INTEGER {
        listen(0),
        connect(1),
        local(2)
      }
      MAX-ACCESS  read-write
      STATUS      current
      DESCRIPTION
              "Defines the type of connection being established
			   Listen for connection, Connect to Host, or Local"
      ::= { ioRelayExtensionCfgEntry 4}
	  
  ioRelayExtCfgHost OBJECT-TYPE
      SYNTAX      DisplayString(SIZE(0..14))
      MAX-ACCESS  read-write
      STATUS      current
      DESCRIPTION
              "The name of the target host."
      ::= { ioRelayExtensionCfgEntry 5}
	  
  ioRelayExtCfgPort OBJECT-TYPE
      SYNTAX      Integer32(0..65535)
      MAX-ACCESS  read-write
      STATUS      current
      DESCRIPTION
              "The port number the target host is listening on for incoming/outgoing connections."
      ::= { ioRelayExtensionCfgEntry 6}
	  
  ioRelayExtCfgLinkChannel OBJECT-TYPE
      SYNTAX      DisplayString(SIZE(0..10))
      MAX-ACCESS  read-write
      STATUS      current
      DESCRIPTION
              "The Link Channel that device would make a connection with.  The link channel is only valid for Local 
			  connection.  The channel must be digital input"
      ::= { ioRelayExtensionCfgEntry 7 }
	  
  ioRelayExtCfgKeepalive OBJECT-TYPE
      SYNTAX      OnOffValue
      MAX-ACCESS  read-write
      STATUS      current
      DESCRIPTION
              "Enables a per-connection TCP keepalive feature; after approximately
               3 minutes of network connection idle time, the connection will send
               a gratuitous ACK to the network peer, either ensuring the connection 
               stays active OR causing a dropped connection condition to be recognized
               by the reverse raw service.
               Applications using this feature need to be aware that there might be 
               some considerable delay between a network disconnection and the port 
               being available for the next connection attempt; this is to allow any 
               data sent on prior connections to be transmitted out of the serial 
               port buffer. Application network retry logic needs to accommodate this feature."
      ::= { ioRelayExtensionCfgEntry 8}
	  
  ioRelayExtCfgMultiHost OBJECT-TYPE
      SYNTAX      OnOffValue
      MAX-ACCESS  read-write
      STATUS      current
      DESCRIPTION
              "Allows user to configure the multihost for client/server initiated connections"
      ::= { ioRelayExtensionCfgEntry 9}
  
  ioRelayExtCfgTunnelName OBJECT-TYPE
      SYNTAX      DisplayString(SIZE(0..14))
      MAX-ACCESS  read-write
      STATUS      current
      DESCRIPTION
              "The name of the HTTP tunnel associated with the Rlogin service."
      ::= { ioRelayExtensionCfgEntry 10 }
  
-- Io extension Relay code ends

-- io Multihost Relay Table

  ioRelayMultihostTable OBJECT-TYPE
      SYNTAX      SEQUENCE OF IoRelayMultihostEntry
      MAX-ACCESS  not-accessible
      STATUS      current
      DESCRIPTION
              "I/O Multihost Table."
      ::= { ioRelayCfg 3 }

  ioRelayMultihostEntry OBJECT-TYPE
      SYNTAX      IoRelayMultihostEntry
      MAX-ACCESS  not-accessible
      STATUS      current
      DESCRIPTION
              "An entry in the ioRelayMultihostEntry, each relating to digital io channel."
      INDEX   { ioRelayMultihostIndex }
      ::= { ioRelayMultihostTable 1 }

  IoRelayMultihostEntry ::=
      SEQUENCE {
        ioRelayMultihostIndex            GenericTableIndex,
        ioRelayMultihostStatus            ContainerStatus,
        ioRelayMultihostMode            INTEGER
        
        }

  ioRelayMultihostIndex OBJECT-TYPE
      SYNTAX      GenericTableIndex
      MAX-ACCESS  not-accessible
      STATUS      current
      DESCRIPTION
              "ioRelayMultihostChanIndex"
      ::= { ioRelayMultihostEntry 1}

  ioRelayMultihostStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioRelayMultihostEntry 2}


  ioRelayMultihostMode OBJECT-TYPE
        SYNTAX      INTEGER {
        all(1),
        backup(2)
      }
      MAX-ACCESS  read-write
      STATUS      current
      DESCRIPTION
              "Set multihost operation mode.all:for muliple host list mode. backup: for primary-backup mode"
      ::= { ioRelayMultihostEntry 4}

-- I/O multihost outbound Relay Table

  ioRelayMultihostOutboundTable OBJECT-TYPE
      SYNTAX      SEQUENCE OF IoRelayMultihostOutboundEntry
      MAX-ACCESS  not-accessible
      STATUS      current
      DESCRIPTION
              "Multihost outbound table."
      ::= {ioRelayCfg 4}
      
  ioRelayMultihostOutboundEntry OBJECT-TYPE
      SYNTAX      IoRelayMultihostOutboundEntry
      MAX-ACCESS  not-accessible
      STATUS      current
      DESCRIPTION
              "An entry in the ioRelayMultihostOutboundTable."
      INDEX   {ioRelayMultihostChanIndex, ioRelayMultihostOutboundIndex }
      ::= { ioRelayMultihostOutboundTable 1 }

  IoRelayMultihostOutboundEntry ::=
      SEQUENCE {
  ioRelayMultihostChanIndex        GenericTableIndex,
  ioRelayMultihostOutboundIndex        GenericTableIndex,
  ioRelayMultihostOutboundStatus        ContainerStatus,
  ioRelayMultihostOutboundHostID        DisplayString,
  ioRelayMultihostOutboundTcpPort        Integer32,
  ioRelayMultihostOutboundTunnel         DisplayString
      }

   ioRelayMultihostChanIndex OBJECT-TYPE
      SYNTAX      GenericTableIndex
      MAX-ACCESS  not-accessible
      STATUS      current
      DESCRIPTION
              "Channel Index"
      ::= { ioRelayMultihostOutboundEntry 1 }

  ioRelayMultihostOutboundIndex OBJECT-TYPE
      SYNTAX      GenericTableIndex
      MAX-ACCESS  not-accessible
      STATUS      current
      DESCRIPTION
              "The outbound entry number"
      ::= { ioRelayMultihostOutboundEntry 2 }

  ioRelayMultihostOutboundStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioRelayMultihostOutboundEntry 3 }


  ioRelayMultihostOutboundHostID OBJECT-TYPE
      SYNTAX      DisplayString (SIZE(0..14))
      MAX-ACCESS  read-write
      STATUS      current
      DESCRIPTION
              "The host name."
      ::= { ioRelayMultihostOutboundEntry 4 }

  ioRelayMultihostOutboundTcpPort OBJECT-TYPE
      SYNTAX      Integer32(0..65535)
      MAX-ACCESS  read-write
      STATUS      current
      DESCRIPTION
              "The host TCP port."
      ::= { ioRelayMultihostOutboundEntry 5 }
	  
  ioRelayMultihostOutboundTunnel OBJECT-TYPE
      SYNTAX      DisplayString (SIZE(0..14))
      MAX-ACCESS  read-write
      STATUS      current
      DESCRIPTION
              "The HTTP tunnel associated with this host."
      ::= { ioRelayMultihostOutboundEntry 6 }
  
-- io Relay multihost outbound Table ends

-- IO Relay SSL Info
  ioRelaySSLTable OBJECT-TYPE
      SYNTAX      SEQUENCE OF IoRelaySSLEntry
      MAX-ACCESS  not-accessible
      STATUS      current
      DESCRIPTION
              "io Relay SSL Table."
      ::= { ioRelayCfg 5 }

  ioRelaySSLEntry OBJECT-TYPE
      SYNTAX      IoRelaySSLEntry
      MAX-ACCESS  not-accessible
      STATUS      current
      DESCRIPTION
              "An entry in the ioRelaySSLEntry, each relating to a io."
      INDEX   { ioRelaySSLIndex }
      ::= { ioRelaySSLTable 1 }
  IoRelaySSLEntry ::=
      SEQUENCE {
  ioRelaySSLIndex        GenericTableIndex,
  ioRelaySSLStatus       ContainerStatus,
  ioRelaySSLEnabled        OnOffValue,
  ioRelaySSLuseServer        OnOffValue,
  ioRelaySSLVersion        INTEGER,
  ioRelaySSLType        INTEGER,
  ioRelaySSLVerifyPeerCertificate        OnOffValue,
  ioRelaySSLCountry        DisplayString,
  ioRelaySSLStateProv        DisplayString,
  ioRelaySSLLocality        DisplayString,
  ioRelaySSLOrganisation        DisplayString,
  ioRelaySSLOrganisationUnit        DisplayString,
  ioRelaySSLCommonName        DisplayString,
  ioRelaySSLEmail        DisplayString
      
      }

  ioRelaySSLIndex OBJECT-TYPE
      SYNTAX      GenericTableIndex
      MAX-ACCESS  not-accessible
      STATUS      current
      DESCRIPTION
              "io Relay SSL Index"
      ::= { ioRelaySSLEntry 1}

  ioRelaySSLStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {ioRelaySSLEntry 2}

  ioRelaySSLEnabled  OBJECT-TYPE
      SYNTAX   OnOffValue
      MAX-ACCESS    read-write
      STATUS        current
      DESCRIPTION
                "Enables/disables SSL."
      ::= {ioRelaySSLEntry 3}

  ioRelaySSLuseServer  OBJECT-TYPE
      SYNTAX   OnOffValue
      MAX-ACCESS    read-write
      STATUS        current
      DESCRIPTION
                "Uses the SSL/TLS server configuration for the line."
      ::= {ioRelaySSLEntry 4}

  ioRelaySSLVersion  OBJECT-TYPE
      SYNTAX      INTEGER {
        any(1),
        tlsv1(2),
        sslv3(3)
      }
      MAX-ACCESS    read-write
      STATUS        current
      DESCRIPTION
                "Specify whether you want to use:
                 Any-The Device Server will try a TLSv1 connection first.
                     If that fails, it will try an SSLv3 connection. 
                     If that fails, it will try an SSLv2 connection.
                 TLSv1-The connection will use only TLSv1.
                 SSLv3-The connection will use only SSLv3.
                 The default is Any."
      ::= {ioRelaySSLEntry 5}

  ioRelaySSLType    OBJECT-TYPE
      SYNTAX      INTEGER {
        client(1),
        server(2)
      }
      MAX-ACCESS    read-write
      STATUS        current
      DESCRIPTION
                "Specify whether the Device Server will act as an 
                 SSL/TLS client or server. The default is Client."
      ::= {ioRelaySSLEntry 6}

  ioRelaySSLVerifyPeerCertificate  OBJECT-TYPE
      SYNTAX   OnOffValue
      MAX-ACCESS    read-write
      STATUS        current
      DESCRIPTION
                "Enable this option when you want the Validation Criteria
                 to match the Peer Certificate for authentication to pass.
                 If you enable this option, you need to download an  
                 SSL/TLS certificate authority (CA) list file to the 
                 Device Server. Any values that are entered in the validation
                 criteria must match the peer certificate for an SSL connection;
                 any fields left blank will not be validated against the peer 
                 certificate."
      ::= {ioRelaySSLEntry 7}

  ioRelaySSLCountry    OBJECT-TYPE
      SYNTAX      DisplayString(SIZE(0..2))
      MAX-ACCESS    read-write
      STATUS        current
      DESCRIPTION
                "A two character country code; for example, US."
      ::= {ioRelaySSLEntry 8}

  ioRelaySSLStateProv    OBJECT-TYPE
      SYNTAX      DisplayString(SIZE(0..128))
      MAX-ACCESS    read-write
      STATUS        current
      DESCRIPTION
                "Up to a 128 character entry for the state/province;
                 for example, IL."
      ::= {ioRelaySSLEntry 9}

  ioRelaySSLLocality    OBJECT-TYPE
      SYNTAX      DisplayString(SIZE(0..128))
      MAX-ACCESS    read-write
      STATUS        current
      DESCRIPTION
                "Up to a 128 character entry for the location; 
                 for example, a city."
      ::= {ioRelaySSLEntry 10}

  ioRelaySSLOrganisation    OBJECT-TYPE
      SYNTAX      DisplayString(SIZE(0..64))
      MAX-ACCESS    read-write
      STATUS        current
      DESCRIPTION
                "Up to a 64 character entry for the organization; 
                 for example, Accounting."
      ::= {ioRelaySSLEntry 11}

  ioRelaySSLOrganisationUnit    OBJECT-TYPE
      SYNTAX      DisplayString(SIZE(0..64))
      MAX-ACCESS    read-write
      STATUS        current
      DESCRIPTION
                "Up to a 64 character entry for the unit in the 
                 organization; for example, Payroll."
      ::= {ioRelaySSLEntry 12}

  ioRelaySSLCommonName    OBJECT-TYPE
      SYNTAX      DisplayString(SIZE(0..64))
      MAX-ACCESS    read-write
      STATUS        current
      DESCRIPTION
                "Up to a 64 character entry for common name; for example,
                 the host name or fully qualified domain name."
      ::= {ioRelaySSLEntry 13}

  ioRelaySSLEmail    OBJECT-TYPE
      SYNTAX      DisplayString(SIZE(0..128))
      MAX-ACCESS    read-write
      STATUS        current
      DESCRIPTION
                "Up to a 64 character entry for an email address; 
                 for example, acct@anycompany.com."
      ::= {ioRelaySSLEntry 14}
	  
-- io SSL Server Cipher Table

  ioRelaySSLCipherTable OBJECT-TYPE
      SYNTAX      SEQUENCE OF IoRelaySSLCipherEntry
      MAX-ACCESS  not-accessible
      STATUS      current
      DESCRIPTION
              "SSL CIpher."
      ::= {ioRelayCfg 6}

  ioRelaySSLCipherEntry OBJECT-TYPE
      SYNTAX      IoRelaySSLCipherEntry
      MAX-ACCESS  not-accessible
      STATUS      current
      DESCRIPTION
              "An entry in the sslCipherTable, each relating to a cipher entry."
      INDEX   { ioRelaySSLChanIndex, ioRelaySSLCipherIndex }
      ::= { ioRelaySSLCipherTable 1 }

  IoRelaySSLCipherEntry ::=
      SEQUENCE {
         ioRelaySSLChanIndex        GenericTableIndex,
         ioRelaySSLCipherIndex       Integer32,
         ioRelaySSLCipherStatus        ContainerStatus,
         ioRelaySSLCipherEncryption        INTEGER,
         ioRelaySSLCipherKeySizeMin        INTEGER,
         ioRelaySSLCipherKeySizeMax        INTEGER,
         ioRelaySSLCipherKeyExchange        INTEGER,
         ioRelaySSLCipherHMAC        INTEGER
      }
      
  ioRelaySSLChanIndex OBJECT-TYPE
      SYNTAX      GenericTableIndex
      MAX-ACCESS  not-accessible
      STATUS      current
      DESCRIPTION
              "The io number"
      ::= { ioRelaySSLCipherEntry 1 }

  ioRelaySSLCipherIndex OBJECT-TYPE
      SYNTAX      Integer32(1..5)
      MAX-ACCESS  not-accessible
      STATUS      current
      DESCRIPTION
              "The cipher priority. 1- highest 5 - lowest."
      ::= { ioRelaySSLCipherEntry 2 }

  ioRelaySSLCipherStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioRelaySSLCipherEntry 3 }

  ioRelaySSLCipherEncryption OBJECT-TYPE
      SYNTAX      INTEGER {
        none(1),
        any(2),
        aes(3),
        tripledes(4),
        des(5),
        arctwo(6),
        arcfour(7)
      }
      MAX-ACCESS  read-write
      STATUS      current
      DESCRIPTION
              "SSL Encryption. None is not allowed for priority 1.
               Any will use the first encryption format that can be 
               negotiated. The default is any."
      ::= { ioRelaySSLCipherEntry 4 }

  ioRelaySSLCipherKeySizeMin OBJECT-TYPE
      SYNTAX      INTEGER {
        min40(1),
        min56(2),
        min64(3),
        min128(4),
        min168(5),
        min256(6)
      }
      MAX-ACCESS  read-write
      STATUS      current
      DESCRIPTION
              "The minimum key size value that will be used for 
               the specified encryption type. The default is 40."
      ::= { ioRelaySSLCipherEntry 5 }

  ioRelaySSLCipherKeySizeMax OBJECT-TYPE
      SYNTAX      INTEGER {
        max40(1),
        max56(2),
        max64(3),
        max128(4),
        max168(5),
        max256(6)
      }
      MAX-ACCESS  read-write
      STATUS      current
      DESCRIPTION
              "The maximum key size value that will be used for the
               specified encryption type. The default is 256."
      ::= { ioRelaySSLCipherEntry 6 }

  ioRelaySSLCipherKeyExchange OBJECT-TYPE
      SYNTAX      INTEGER {
        any(1),
        rsa(2),
        edhrsa(3),
        edhdss(4),
        adh(5)
      }
      MAX-ACCESS  read-write
      STATUS      current
      DESCRIPTION
              "The type of key to exchange for the encryption format:
               Any-Any key exchange that is valid is used (this does 
                   not, however, include ADH keys).
               RSA-This is an RSA key exchange using an RSA key and 
                   certificate.
               EDHRSA-This is an EDH key exchange using an RSA key 
                   and certificate.
               EDHDSS-This is an EDH key exchange using a DSA key
                   and certificate.
               ADH-This is an anonymous key exchange which does not 
                   require a private key or certificate. Choose this 
                   key if you do not want to authenticate the peer device, 
                   but you want the data encrypted on the SSL/TLS connection.
               The default is Any."
      ::= { ioRelaySSLCipherEntry 7 }

  ioRelaySSLCipherHMAC OBJECT-TYPE
      SYNTAX      INTEGER {
        any(1),
        sha(2),
        md5(3)
      }
      MAX-ACCESS  read-write
      STATUS      current
      DESCRIPTION
              "Select the key-hashing for message authentication method 
               for your encryption type: Any, MD5, or SHA1.
               The default is Any."
      ::= { ioRelaySSLCipherEntry 8 }
      

  -- IO SSL Server Cipher Table ENDS
      
-- I/O Relay Cfg ENDS      

  -- I/O LineSignal config BEGINS
  ioLineSignalCfgTable OBJECT-TYPE
      SYNTAX      SEQUENCE OF IoLineSignalCfgEntry
      MAX-ACCESS  not-accessible
      STATUS      current
      DESCRIPTION
              "ioLineSignalCfgTable."
      ::= { ioLineSignalCfg 1 }

  ioLineSignalCfgEntry OBJECT-TYPE
      SYNTAX      IoLineSignalCfgEntry
      MAX-ACCESS  not-accessible
      STATUS      current
      DESCRIPTION
              "An entry in the ioLineSignalCfgTable"
      INDEX   { ioLineSignalCfgPortIndex, ioLineSignalCfgSignalIndex}
      ::= { ioLineSignalCfgTable 1 }

  IoLineSignalCfgEntry ::= 
      SEQUENCE {
        ioLineSignalCfgPortIndex          GenericTableIndex,
        ioLineSignalCfgSignalIndex          INTEGER,
        ioLineSignalCfgStatus          ContainerStatus,
        ioLineSignalCfgResourceType          INTEGER,
        ioLineSignalCfgEnable          OnOffValue,
        ioLineSignalCfgDescription          DisplayString,
        ioLineSignalInputCfgLatch          INTEGER,
        ioLineSignalInputCfgInvertSignal          OnOffValue,
        ioLineSignalInputCfgAlarmTrigger          INTEGER,
        ioLineSignalInputCfgAlarmClear          INTEGER,
        ioLineSignalInputCfgAlarmEmail          OnOffValue,
        ioLineSignalInputCfgAlarmSyslog          OnOffValue,
        ioLineSignalInputCfgAlarmSNMP          OnOffValue,
        ioLineSignalOutputCfgFailsafe          INTEGER
      }

  ioLineSignalCfgPortIndex OBJECT-TYPE
      SYNTAX      GenericTableIndex
      MAX-ACCESS  not-accessible
      STATUS      current
      DESCRIPTION
              "Index of the associated serial port"
      ::= { ioLineSignalCfgEntry 1 }

  ioLineSignalCfgSignalIndex OBJECT-TYPE
      SYNTAX      INTEGER {
          dsr(1),
          dcd(2),
          cts(3),
          dtr(4),
          rts(5)
      }
          
      MAX-ACCESS  not-accessible
      STATUS      current
      DESCRIPTION
              "Index of the associate line signal"
      ::= { ioLineSignalCfgEntry 2 }
      
  ioLineSignalCfgStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioLineSignalCfgEntry 3 }

  ioLineSignalCfgResourceType OBJECT-TYPE
      SYNTAX      INTEGER {
         input(2),   
         output(3)
      }
      MAX-ACCESS  read-only
      STATUS      current
      DESCRIPTION
              "Signifies whether this resource is input or output"
      ::= { ioLineSignalCfgEntry 4 }
      
  ioLineSignalCfgEnable OBJECT-TYPE
      SYNTAX      OnOffValue
      MAX-ACCESS  read-write
      STATUS      current
      DESCRIPTION
              "Enable/disable this resource"
      ::= { ioLineSignalCfgEntry 5 }

  ioLineSignalCfgDescription OBJECT-TYPE
      SYNTAX      DisplayString(SIZE(0..20))
      MAX-ACCESS  read-write
      STATUS      current
      DESCRIPTION
              "Description for this resource"
      ::= { ioLineSignalCfgEntry 6 }

  ioLineSignalInputCfgLatch OBJECT-TYPE
      SYNTAX      INTEGER {
         disabled(1),
         inactiveToActive(2),
         activeToInactive(3)
      }
      MAX-ACCESS  read-write
      STATUS      current
      DESCRIPTION
              "Line Signal (input): Latch mode"
      ::= { ioLineSignalCfgEntry 7 }

  ioLineSignalInputCfgInvertSignal OBJECT-TYPE
      SYNTAX      OnOffValue
      MAX-ACCESS  read-write
      STATUS      current
      DESCRIPTION
              "Line Signal (input): Enable/disable signal inversion"
      ::= { ioLineSignalCfgEntry 8 }

  ioLineSignalInputCfgAlarmTrigger OBJECT-TYPE
      SYNTAX      INTEGER {
        disabled(1),
        low(2),
        high(3)
      }
      MAX-ACCESS  read-write
      STATUS      current
      DESCRIPTION
              "Line Signal (input): Alarm trigger type"
      ::= { ioLineSignalCfgEntry 9 }
      
  ioLineSignalInputCfgAlarmClear OBJECT-TYPE
      SYNTAX      INTEGER {
        auto(1),
        manual(2)
      }
      MAX-ACCESS  read-write
      STATUS      current
      DESCRIPTION
              "Line Signal (input): Alarm clear type"
      ::= { ioLineSignalCfgEntry 10 }
      
  ioLineSignalInputCfgAlarmEmail OBJECT-TYPE
      SYNTAX      OnOffValue
      MAX-ACCESS  read-write
      STATUS      current
      DESCRIPTION
              "Line Signal (input): Enable/disable email alert on alarm trigger"
      ::= { ioLineSignalCfgEntry 11 }
      
  ioLineSignalInputCfgAlarmSyslog OBJECT-TYPE
      SYNTAX      OnOffValue
      MAX-ACCESS  read-write
      STATUS      current
      DESCRIPTION
              "Line Signal (input): Enable/disable syslog alert on alarm trigger"
      ::= { ioLineSignalCfgEntry 12 }
      
  ioLineSignalInputCfgAlarmSNMP OBJECT-TYPE
      SYNTAX      OnOffValue
      MAX-ACCESS  read-write
      STATUS      current
      DESCRIPTION
              "Line Signal (input): Enable/disable SNMP alert on alarm trigger"
      ::= { ioLineSignalCfgEntry 13 }
      

  ioLineSignalOutputCfgFailsafe OBJECT-TYPE
      SYNTAX      INTEGER {
          none(1),
          activateOutput(2),
          deactivateOutput(3)
      }
      MAX-ACCESS  read-write
      STATUS      current
      DESCRIPTION
              "Line Signal (output): Action to take when failsafe timer expires"
      ::= { ioLineSignalCfgEntry 14 }
	  
-- I/O Line extension code start
	  
  ioLineExtensionSigCfgTable OBJECT-TYPE
      SYNTAX      SEQUENCE OF IoLineExtensionSigCfgEntry
      MAX-ACCESS  not-accessible
      STATUS      current
      DESCRIPTION
              "ioLineExtensionSigCfgTable"
      ::= { ioLineSignalCfg 2 }

  ioLineExtensionSigCfgEntry OBJECT-TYPE
      SYNTAX      IoLineExtensionSigCfgEntry
      MAX-ACCESS  not-accessible
      STATUS      current
      DESCRIPTION
              "An entry in the ioLineExtensionCfgTable"
      INDEX   { ioLineExtSigCfgChanIndex }
      ::= { ioLineExtensionSigCfgTable 1 }

  IoLineExtensionSigCfgEntry ::=
      SEQUENCE {
         ioLineExtSigCfgChanIndex            GenericTableIndex,
         ioLineExtSigCfgStatus			ContainerStatus,		
         ioLineExtSigCfgEnable          OnOffValue,
         ioLineExtSigCfgConnMethod            INTEGER,
         ioLineExtSigCfgHost			DisplayString,
         ioLineExtSigCfgPort            Integer32,
         ioLineExtSigCfgLinkChannel			DisplayString,
         ioLineExtSigCfgKeepalive          	OnOffValue,
         ioLineExtSigCfgMultiHost          	OnOffValue,
         ioLineExtSigCfgTunnelName      DisplayString
      }

  ioLineExtSigCfgChanIndex OBJECT-TYPE
      SYNTAX      GenericTableIndex
      MAX-ACCESS  not-accessible
      STATUS      current
      DESCRIPTION
              "I/O resource index"
      ::= { ioLineExtensionSigCfgEntry 1 }
   
  ioLineExtSigCfgStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioLineExtensionSigCfgEntry 2 }
	  
  ioLineExtSigCfgEnable OBJECT-TYPE
      SYNTAX      OnOffValue
      MAX-ACCESS  read-write
      STATUS      current
      DESCRIPTION
              "Enable/disable this digital  I/O Extension"
      ::= { ioLineExtensionSigCfgEntry 3 }
	  
  ioLineExtSigCfgConnMethod OBJECT-TYPE
      SYNTAX      INTEGER {
        listen(0),
        connect(1),
        local(2)
      }
      MAX-ACCESS  read-write
      STATUS      current
      DESCRIPTION
              "Defines the type of connection being established
			   Listen for connection, Connect to Host, or Local"
      ::= { ioLineExtensionSigCfgEntry 4}
	  
  ioLineExtSigCfgHost OBJECT-TYPE
      SYNTAX      DisplayString(SIZE(0..14))
      MAX-ACCESS  read-write
      STATUS      current
      DESCRIPTION
              "The name of the target host."
      ::= { ioLineExtensionSigCfgEntry 5}
	  
  ioLineExtSigCfgPort OBJECT-TYPE
      SYNTAX      Integer32(0..65535)
      MAX-ACCESS  read-write
      STATUS      current
      DESCRIPTION
              "The port number the target host is listening on for incoming/outgoing connections."
      ::= { ioLineExtensionSigCfgEntry 6}
	  
  ioLineExtSigCfgLinkChannel OBJECT-TYPE
      SYNTAX      DisplayString(SIZE(0..10))
      MAX-ACCESS  read-write
      STATUS      current
      DESCRIPTION
              "The Link Channel that device would make a connection with.  The link channel is only valid for Local 
			  connection.  The channel must be digital input"
      ::= { ioLineExtensionSigCfgEntry 7 }
	  
  ioLineExtSigCfgKeepalive OBJECT-TYPE
      SYNTAX      OnOffValue
      MAX-ACCESS  read-write
      STATUS      current
      DESCRIPTION
              "Enables a per-connection TCP keepalive feature; after approximately
               3 minutes of network connection idle time, the connection will send
               a gratuitous ACK to the network peer, either ensuring the connection 
               stays active OR causing a dropped connection condition to be recognized
               by the reverse raw service.
               Applications using this feature need to be aware that there might be 
               some considerable delay between a network disconnection and the port 
               being available for the next connection attempt; this is to allow any 
               data sent on prior connections to be transmitted out of the serial 
               port buffer. Application network retry logic needs to accommodate this feature."
      ::= { ioLineExtensionSigCfgEntry 8}
	
  ioLineExtSigCfgMultiHost OBJECT-TYPE
      SYNTAX      OnOffValue
      MAX-ACCESS  read-write
      STATUS      current
      DESCRIPTION
              "Allows user to configure the multihost for client/server initiated connections"
      ::= { ioLineExtensionSigCfgEntry 9}
  
  ioLineExtSigCfgTunnelName OBJECT-TYPE
      SYNTAX      DisplayString(SIZE(0..14))
      MAX-ACCESS  read-write
      STATUS      current
      DESCRIPTION
              "The name of the HTTP tunnel associated with the Rlogin service."
      ::= { ioLineExtensionSigCfgEntry 10 }
  
-- Io extension code ends

-- io Multihost Line Signal Table
  ioLineMultihostSigTable OBJECT-TYPE
      SYNTAX      SEQUENCE OF IoLineMultihostSigEntry
      MAX-ACCESS  not-accessible
      STATUS      current
      DESCRIPTION
              "I/O Multihost Table."
      ::= { ioLineSignalCfg 3 }

  ioLineMultihostSigEntry OBJECT-TYPE
      SYNTAX      IoLineMultihostSigEntry
      MAX-ACCESS  not-accessible
      STATUS      current
      DESCRIPTION
              "An entry in the ioLineMultihostEntry, each relating to digital io channel."
      INDEX   { ioLineMultihostSigIndex }
      ::= { ioLineMultihostSigTable 1 }

  IoLineMultihostSigEntry ::=
      SEQUENCE {
        ioLineMultihostSigIndex            GenericTableIndex,
        ioLineMultihostSigStatus          ContainerStatus,
        ioLineMultihostModeSig            INTEGER
        
        }

  ioLineMultihostSigIndex OBJECT-TYPE
      SYNTAX      GenericTableIndex
      MAX-ACCESS  not-accessible
      STATUS      current
      DESCRIPTION
              "ioLineMultihostSigIndex"
      ::= { ioLineMultihostSigEntry 1}

  ioLineMultihostSigStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioLineMultihostSigEntry 2}

  ioLineMultihostModeSig OBJECT-TYPE
        SYNTAX      INTEGER {
        all(1),
        backup(2)
      }
      MAX-ACCESS  read-write
      STATUS      current
      DESCRIPTION
              "Set multihost operation mode.all:for muliple host list mode. backup: for primary-backup mode"
      ::= { ioLineMultihostSigEntry 4}

-- I/O multihost outbound Table

  ioLineMultihostOutboundSigTable OBJECT-TYPE
      SYNTAX      SEQUENCE OF IoLineMultihostOutboundSigEntry
      MAX-ACCESS  not-accessible
      STATUS      current
      DESCRIPTION
              "Multihost outbound table."
      ::= {ioLineSignalCfg 4}
      
  ioLineMultihostOutboundSigEntry OBJECT-TYPE
      SYNTAX      IoLineMultihostOutboundSigEntry
      MAX-ACCESS  not-accessible
      STATUS      current
      DESCRIPTION
              "An entry in the ioLineMultihostOutboundTable."
      INDEX   {ioLineMultihostSigChanIndex, ioLineMultihostOutboundSigIndex }
      ::= { ioLineMultihostOutboundSigTable 1 }

  IoLineMultihostOutboundSigEntry ::=
    SEQUENCE {
       ioLineMultihostSigChanIndex        GenericTableIndex,
       ioLineMultihostOutboundSigIndex        GenericTableIndex,
       ioLineMultihostOutboundSigStatus        ContainerStatus,
       ioLineMultihostOutboundSigHostID        DisplayString,
       ioLineMultihostOutboundSigTcpPort        Integer32,
       ioLineMultihostOutboundSigTunnel        DisplayString
    }

   ioLineMultihostSigChanIndex OBJECT-TYPE
      SYNTAX      GenericTableIndex
      MAX-ACCESS  not-accessible
      STATUS      current
      DESCRIPTION
              "Channel Index"
      ::= { ioLineMultihostOutboundSigEntry 1 }
   
  ioLineMultihostOutboundSigIndex OBJECT-TYPE
      SYNTAX      GenericTableIndex
      MAX-ACCESS  not-accessible
      STATUS      current
      DESCRIPTION
              "The outbound entry number"
      ::= { ioLineMultihostOutboundSigEntry 2 }

  ioLineMultihostOutboundSigStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioLineMultihostOutboundSigEntry 3 }


  ioLineMultihostOutboundSigHostID OBJECT-TYPE
      SYNTAX      DisplayString (SIZE(0..14))
      MAX-ACCESS  read-write
      STATUS      current
      DESCRIPTION
              "The host name."
      ::= { ioLineMultihostOutboundSigEntry 4 }

  ioLineMultihostOutboundSigTcpPort OBJECT-TYPE
      SYNTAX      Integer32(0..65535)
      MAX-ACCESS  read-write
      STATUS      current
      DESCRIPTION
              "The host TCP port."
      ::= { ioLineMultihostOutboundSigEntry 5 }
  
  ioLineMultihostOutboundSigTunnel OBJECT-TYPE
      SYNTAX      DisplayString (SIZE(0..14))
      MAX-ACCESS  read-write
      STATUS      current
      DESCRIPTION
              "The HTTP tunnel associated with this host."
      ::= { ioLineMultihostOutboundSigEntry 6 }
  
	  
-- io multihost outbound Table Line Signal ENDS
-- IO SSL Line Signal Info
  ioLineSSLSigTable OBJECT-TYPE
      SYNTAX      SEQUENCE OF IoLineSSLSigEntry
      MAX-ACCESS  not-accessible
      STATUS      current
      DESCRIPTION
              "io SSL Table."
      ::= { ioLineSignalCfg 5 }

  ioLineSSLSigEntry OBJECT-TYPE
      SYNTAX      IoLineSSLSigEntry
      MAX-ACCESS  not-accessible
      STATUS      current
      DESCRIPTION
              "An entry in the ioDigitalSSLEntry, each relating to a io."
      INDEX   { ioLineSSLSigIndex }
      ::= { ioLineSSLSigTable 1 }
   
  IoLineSSLSigEntry ::=
      SEQUENCE {
  ioLineSSLSigIndex        GenericTableIndex,
  ioLineSSLSigStatus       ContainerStatus,
  ioLineSSLSigEnabled        OnOffValue,
  ioLineSSLSiguseServer        OnOffValue,
  ioLineSSLSigVersion        INTEGER,
  ioLineSSLSigType        INTEGER,
  ioLineSSLSigVerifyPeerCertificate        OnOffValue,
  ioLineSSLSigCountry        DisplayString,
  ioLineSSLSigStateProv        DisplayString,
  ioLineSSLSigLocality        DisplayString,
  ioLineSSLSigOrganisation        DisplayString,
  ioLineSSLSigOrganisationUnit        DisplayString,
  ioLineSSLSigCommonName        DisplayString,
  ioLineSSLSigEmail        DisplayString     
      }

  ioLineSSLSigIndex OBJECT-TYPE
      SYNTAX      GenericTableIndex
      MAX-ACCESS  not-accessible
      STATUS      current
      DESCRIPTION
              "io SSL Index"
      ::= { ioLineSSLSigEntry 1}
   
  ioLineSSLSigStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {ioLineSSLSigEntry 2}

  ioLineSSLSigEnabled  OBJECT-TYPE
      SYNTAX   OnOffValue
      MAX-ACCESS    read-write
      STATUS        current
      DESCRIPTION
                "Enables/disables SSL."
      ::= {ioLineSSLSigEntry 3}

  ioLineSSLSiguseServer  OBJECT-TYPE
      SYNTAX   OnOffValue
      MAX-ACCESS    read-write
      STATUS        current
      DESCRIPTION
                "Uses the SSL/TLS server configuration for the line."
      ::= {ioLineSSLSigEntry 4}

  ioLineSSLSigVersion  OBJECT-TYPE
      SYNTAX      INTEGER {
        any(1),
        tlsv1(2),
        sslv3(3)
      }
      MAX-ACCESS    read-write
      STATUS        current
      DESCRIPTION
                "Specify whether you want to use:
                 Any-The Device Server will try a TLSv1 connection first.
                     If that fails, it will try an SSLv3 connection. 
                     If that fails, it will try an SSLv2 connection.
                 TLSv1-The connection will use only TLSv1.
                 SSLv3-The connection will use only SSLv3.
                 The default is Any."
      ::= {ioLineSSLSigEntry 5}

  ioLineSSLSigType    OBJECT-TYPE
      SYNTAX      INTEGER {
        client(1),
        server(2)
      }
      MAX-ACCESS    read-write
      STATUS        current
      DESCRIPTION
                "Specify whether the Device Server will act as an 
                 SSL/TLS client or server. The default is Client."
      ::= {ioLineSSLSigEntry 6}

  ioLineSSLSigVerifyPeerCertificate  OBJECT-TYPE
      SYNTAX   OnOffValue
      MAX-ACCESS    read-write
      STATUS        current
      DESCRIPTION
                "Enable this option when you want the Validation Criteria
                 to match the Peer Certificate for authentication to pass.
                 If you enable this option, you need to download an  
                 SSL/TLS certificate authority (CA) list file to the 
                 Device Server. Any values that are entered in the validation
                 criteria must match the peer certificate for an SSL connection;
                 any fields left blank will not be validated against the peer 
                 certificate."
      ::= {ioLineSSLSigEntry 7}

  ioLineSSLSigCountry    OBJECT-TYPE
      SYNTAX      DisplayString(SIZE(0..2))
      MAX-ACCESS    read-write
      STATUS        current
      DESCRIPTION
                "A two character country code; for example, US."
      ::= {ioLineSSLSigEntry 8}

  ioLineSSLSigStateProv    OBJECT-TYPE
      SYNTAX      DisplayString(SIZE(0..128))
      MAX-ACCESS    read-write
      STATUS        current
      DESCRIPTION
                "Up to a 128 character entry for the state/province;
                 for example, IL."
      ::= {ioLineSSLSigEntry 9}

  ioLineSSLSigLocality    OBJECT-TYPE
      SYNTAX      DisplayString(SIZE(0..128))
      MAX-ACCESS    read-write
      STATUS        current
      DESCRIPTION
                "Up to a 128 character entry for the location; 
                 for example, a city."
      ::= {ioLineSSLSigEntry 10}

  ioLineSSLSigOrganisation    OBJECT-TYPE
      SYNTAX      DisplayString(SIZE(0..64))
      MAX-ACCESS    read-write
      STATUS        current
      DESCRIPTION
                "Up to a 64 character entry for the organization; 
                 for example, Accounting."
      ::= {ioLineSSLSigEntry 11}

  ioLineSSLSigOrganisationUnit    OBJECT-TYPE
      SYNTAX      DisplayString(SIZE(0..64))
      MAX-ACCESS    read-write
      STATUS        current
      DESCRIPTION
                "Up to a 64 character entry for the unit in the 
                 organization; for example, Payroll."
      ::= {ioLineSSLSigEntry 12}

  ioLineSSLSigCommonName    OBJECT-TYPE
      SYNTAX      DisplayString(SIZE(0..64))
      MAX-ACCESS    read-write
      STATUS        current
      DESCRIPTION
                "Up to a 64 character entry for common name; for example,
                 the host name or fully qualified domain name."
      ::= {ioLineSSLSigEntry 13}

  ioLineSSLSigEmail    OBJECT-TYPE
      SYNTAX      DisplayString(SIZE(0..128))
      MAX-ACCESS    read-write
      STATUS        current
      DESCRIPTION
                "Up to a 64 character entry for an email address; 
                 for example, acct@anycompany.com."
      ::= {ioLineSSLSigEntry 14}
	  

-- io SSL Line Signal Cipher Table

  ioLineSSLSigCipherTable OBJECT-TYPE
      SYNTAX      SEQUENCE OF IoLineSSLSigCipherEntry
      MAX-ACCESS  not-accessible
      STATUS      current
      DESCRIPTION
              "SSL CIpher."
      ::= {ioLineSignalCfg 6}

  ioLineSSLSigCipherEntry OBJECT-TYPE
      SYNTAX      IoLineSSLSigCipherEntry
      MAX-ACCESS  not-accessible
      STATUS      current
      DESCRIPTION
              "An entry in the sslCipherTable, each relating to a cipher entry."
      INDEX   { ioLineSSLSigChanIndex, ioLineSSLSigCipherIndex }
      ::= { ioLineSSLSigCipherTable 1 }

  IoLineSSLSigCipherEntry ::=
     SEQUENCE {
  	ioLineSSLSigChanIndex        GenericTableIndex,
        ioLineSSLSigCipherIndex       Integer32,
        ioLineSSLSigCipherStatus        ContainerStatus,
        ioLineSSLSigCipherEncryption        INTEGER,
        ioLineSSLSigCipherKeySizeMin        INTEGER,
        ioLineSSLSigCipherKeySizeMax        INTEGER,
        ioLineSSLSigCipherKeyExchange        INTEGER,
        ioLineSSLSigCipherHMAC        INTEGER
     }

  ioLineSSLSigChanIndex OBJECT-TYPE
      SYNTAX      GenericTableIndex
      MAX-ACCESS  not-accessible
      STATUS      current
      DESCRIPTION
              "The io number"
      ::= { ioLineSSLSigCipherEntry 1 }
   
  ioLineSSLSigCipherIndex OBJECT-TYPE
      SYNTAX      Integer32(1..5)
      MAX-ACCESS  not-accessible
      STATUS      current
      DESCRIPTION
              "The cipher priority. 1- highest 5 - lowest."
      ::= { ioLineSSLSigCipherEntry 2 }

  ioLineSSLSigCipherStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ioLineSSLSigCipherEntry 3 }

  ioLineSSLSigCipherEncryption OBJECT-TYPE
      SYNTAX      INTEGER {
        none(1),
        any(2),
        aes(3),
        tripledes(4),
        des(5),
        arctwo(6),
        arcfour(7)
      }
      MAX-ACCESS  read-write
      STATUS      current
      DESCRIPTION
              "SSL Encryption. None is not allowed for priority 1.
               Any will use the first encryption format that can be 
               negotiated. The default is any."
      ::= { ioLineSSLSigCipherEntry 4 }

  ioLineSSLSigCipherKeySizeMin OBJECT-TYPE
      SYNTAX      INTEGER {
        min40(1),
        min56(2),
        min64(3),
        min128(4),
        min168(5),
        min256(6)
      }
      MAX-ACCESS  read-write
      STATUS      current
      DESCRIPTION
              "The minimum key size value that will be used for 
               the specified encryption type. The default is 40."
      ::= { ioLineSSLSigCipherEntry 5 }

  ioLineSSLSigCipherKeySizeMax OBJECT-TYPE
      SYNTAX      INTEGER {
        max40(1),
        max56(2),
        max64(3),
        max128(4),
        max168(5),
        max256(6)
      }
      MAX-ACCESS  read-write
      STATUS      current
      DESCRIPTION
              "The maximum key size value that will be used for the
               specified encryption type. The default is 256."
      ::= { ioLineSSLSigCipherEntry 6 }

  ioLineSSLSigCipherKeyExchange OBJECT-TYPE
      SYNTAX      INTEGER {
        any(1),
        rsa(2),
        edhrsa(3),
        edhdss(4),
        adh(5)
      }
      MAX-ACCESS  read-write
      STATUS      current
      DESCRIPTION
              "The type of key to exchange for the encryption format:
               Any-Any key exchange that is valid is used (this does 
                   not, however, include ADH keys).
               RSA-This is an RSA key exchange using an RSA key and 
                   certificate.
               EDHRSA-This is an EDH key exchange using an RSA key 
                   and certificate.
               EDHDSS-This is an EDH key exchange using a DSA key
                   and certificate.
               ADH-This is an anonymous key exchange which does not 
                   require a private key or certificate. Choose this 
                   key if you do not want to authenticate the peer device, 
                   but you want the data encrypted on the SSL/TLS connection.
               The default is Any."
      ::= { ioLineSSLSigCipherEntry 7 }

  ioLineSSLSigCipherHMAC OBJECT-TYPE
      SYNTAX      INTEGER {
        any(1),
        sha(2),
        md5(3)
      }
      MAX-ACCESS  read-write
      STATUS      current
      DESCRIPTION
              "Select the key-hashing for message authentication method 
               for your encryption type: Any, MD5, or SHA1.
               The default is Any."
      ::= { ioLineSSLSigCipherEntry 8 }
      

  -- IO SSL LineSignal Cipher Table ENDS
      
-- I/O LineSignal Cfg ENDS

  ioChannelFunction OBJECT-TYPE
      SYNTAX      INTEGER {
        none(1),
        killall(2)
      }
      MAX-ACCESS  read-write
      STATUS      current
      DESCRIPTION
              "killall - Apply configuration changes to all channels"
      ::= { ioChannelStatus 1 } 


 ioAnalogStatus       OBJECT IDENTIFIER ::= { ioChannelStatus 2 }
 ioDigitalStatus      OBJECT IDENTIFIER ::= { ioChannelStatus 3 }
 ioRelayStatus        OBJECT IDENTIFIER ::= { ioChannelStatus 4 }
 ioLineSignalStatus   OBJECT IDENTIFIER ::= { ioChannelStatus 5 }
      
      -- I/O Analog status BEGINS
  ioAnalogStatusTable OBJECT-TYPE
      SYNTAX      SEQUENCE OF IoAnalogStatusEntry
      MAX-ACCESS  not-accessible
      STATUS      current
      DESCRIPTION
              "ioAnalogStatusTable."
      ::= { ioAnalogStatus 1 }

  ioAnalogStatusEntry OBJECT-TYPE
      SYNTAX      IoAnalogStatusEntry
      MAX-ACCESS  not-accessible
      STATUS      current
      DESCRIPTION
              "An entry in the ioAnalogStatusTable"
      INDEX   { ioAnalogStatusChannelIndex }
      ::= { ioAnalogStatusTable 1 }

  IoAnalogStatusEntry ::= 
      SEQUENCE {
        ioAnalogStatusChannelIndex          GenericTableIndex,
        ioAnalogStatusEnabled          OnOffValue,
        ioAnalogStatusDescription          DisplayString,
        ioAnalogFunction          INTEGER,
        ioAnalogStatusInputState          INTEGER,
        ioAnalogStatusValue          DisplayString,
        ioAnalogStatusMinimum          DisplayString,
        ioAnalogStatusMaximum          DisplayString,
        ioAnalogStatusAlarmLevel          Integer32
      }

  ioAnalogStatusChannelIndex OBJECT-TYPE
      SYNTAX      GenericTableIndex
      MAX-ACCESS  not-accessible
      STATUS      current
      DESCRIPTION
              "Index"
      ::= { ioAnalogStatusEntry 1 }

  ioAnalogStatusEnabled OBJECT-TYPE
      SYNTAX      OnOffValue
      MAX-ACCESS  read-only
      STATUS      current
      DESCRIPTION
              "Enabled"
      ::= { ioAnalogStatusEntry 2 }
      
  ioAnalogStatusDescription OBJECT-TYPE
      SYNTAX      DisplayString(SIZE(0..20))
      MAX-ACCESS  read-only
      STATUS      current
      DESCRIPTION
              "Description"
      ::= { ioAnalogStatusEntry 3 }
      
  ioAnalogFunction OBJECT-TYPE
      SYNTAX      INTEGER {
        none(1),
        kill(2),
        clearAlarm(6),
        clearMin(7),
        clearMax(8)
      }
      MAX-ACCESS  read-write
      STATUS      current
      DESCRIPTION
              "kill - Apply configuration changes to this entry"
      ::= { ioAnalogStatusEntry 4 }

  ioAnalogStatusInputState OBJECT-TYPE
    SYNTAX      INTEGER {
        normal(1),
        open(2),
        short(3)
      }
      MAX-ACCESS  read-only
      STATUS      current
      DESCRIPTION
              "Input state."
      ::= { ioAnalogStatusEntry 5 }     
      
  ioAnalogStatusValue OBJECT-TYPE
      SYNTAX      DisplayString
      MAX-ACCESS  read-only
      STATUS      current
      DESCRIPTION
              "Current analog input value."
      ::= { ioAnalogStatusEntry 6 }

  ioAnalogStatusMinimum OBJECT-TYPE
      SYNTAX      DisplayString
      MAX-ACCESS  read-only
      STATUS      current
      DESCRIPTION
              "Minimum analog input value."
      ::= { ioAnalogStatusEntry 7 }
      
  ioAnalogStatusMaximum OBJECT-TYPE
      SYNTAX      DisplayString
      MAX-ACCESS  read-only
      STATUS      current
      DESCRIPTION
              "Maximum analog input value."
      ::= { ioAnalogStatusEntry 8 }

  ioAnalogStatusAlarmLevel OBJECT-TYPE
      SYNTAX      Integer32(0..5)
      MAX-ACCESS  read-only
      STATUS      current
      DESCRIPTION
              "Alarm level."
      ::= { ioAnalogStatusEntry 9 }
      
  -- I/O Analog status ENDS 
  
  -- I/O Digital status BEGINS
  ioDigitalStatusTable OBJECT-TYPE
      SYNTAX      SEQUENCE OF IoDigitalStatusEntry
      MAX-ACCESS  not-accessible
      STATUS      current
      DESCRIPTION
              "ioDigitalStatusTable."
      ::= { ioDigitalStatus 1 }

  ioDigitalStatusEntry OBJECT-TYPE
      SYNTAX      IoDigitalStatusEntry
      MAX-ACCESS  not-accessible
      STATUS      current
      DESCRIPTION
              "An entry in the ioDigitalStatusTable"
      INDEX   { ioDigitalStatusChannelIndex }
      ::= { ioDigitalStatusTable 1 }

  IoDigitalStatusEntry ::= 
      SEQUENCE {
        ioDigitalStatusChannelIndex         GenericTableIndex,
        ioDigitalStatusEnabled          OnOffValue,
        ioDigitalStatusDescription          DisplayString,
        ioDigitalStatusType          INTEGER,
        ioDigitalFunction          INTEGER,
        ioDigitalStatusState          INTEGER,
        ioDigitalStatusLatchedInputState          INTEGER,
        ioDigitalStatusInputAlarm          INTEGER,
        ioDigitalStatusExtensionState          INTEGER
      }

  ioDigitalStatusChannelIndex OBJECT-TYPE
      SYNTAX      GenericTableIndex
      MAX-ACCESS  not-accessible
      STATUS      current
      DESCRIPTION
              "Index"
      ::= { ioDigitalStatusEntry 1 }

  ioDigitalStatusEnabled OBJECT-TYPE
      SYNTAX      OnOffValue
      MAX-ACCESS  read-only
      STATUS      current
      DESCRIPTION
              "Enabled"
      ::= { ioDigitalStatusEntry 2 }
      
  ioDigitalStatusDescription OBJECT-TYPE
      SYNTAX      DisplayString(SIZE(0..20))
      MAX-ACCESS  read-only
      STATUS      current
      DESCRIPTION
              "Description"
      ::= { ioDigitalStatusEntry 3 }
      
      

  ioDigitalStatusType OBJECT-TYPE
      SYNTAX      INTEGER {
        unknown(1),
        input(2),
        output(3)
      }
      MAX-ACCESS  read-only
      STATUS      current
      DESCRIPTION
              "Resource type"
      ::= { ioDigitalStatusEntry 4 }
      
  ioDigitalFunction OBJECT-TYPE
      SYNTAX      INTEGER {
        none(1),
        kill(2),
        activateOutput(3),
        deactivateOutput(4),
        clearInputLatch(5),
        clearAlarmLatch(6)        
      }
      MAX-ACCESS  read-write
      STATUS      current
      DESCRIPTION
              "kill - Apply configuration changes to this entry"
      ::= { ioDigitalStatusEntry 5 }
  ioDigitalStatusState OBJECT-TYPE
      SYNTAX      INTEGER {
        inactive(1),
        active(2)
      }
      MAX-ACCESS  read-write
      STATUS      current
      DESCRIPTION
              "Digital State.  ."
      ::= { ioDigitalStatusEntry 6 }
  ioDigitalStatusLatchedInputState OBJECT-TYPE
      SYNTAX      INTEGER {
        none(1),
        inactiveToActive(2),
        activeToInactive(3)
      }
      MAX-ACCESS  read-only
      STATUS      current
      DESCRIPTION
              "For digital inputs only."
      ::= { ioDigitalStatusEntry 7 }

  ioDigitalStatusInputAlarm OBJECT-TYPE
      SYNTAX      INTEGER {
        notTriggered(1),
        triggered(2)
      }
      MAX-ACCESS  read-only
      STATUS      current
      DESCRIPTION
              "LineSignal State.  ."
      ::= { ioDigitalStatusEntry 8 }
	  
  ioDigitalStatusExtensionState OBJECT-TYPE
      SYNTAX      INTEGER {
        disable(1),
        enabledDisconnected(2),
        connected(3),
		notAvailable(4)
      }
      MAX-ACCESS  read-only
      STATUS      current
      DESCRIPTION
              "For digital inputs and outputs only."
      ::= { ioDigitalStatusEntry 9 }

   -- I/O Digital status ENDS 
      
  -- I/O Relay status BEGINS
  ioRelayStatusTable OBJECT-TYPE
      SYNTAX      SEQUENCE OF IoRelayStatusEntry
      MAX-ACCESS  not-accessible
      STATUS      current
      DESCRIPTION
              "ioRelayStatusTable."
      ::= { ioRelayStatus 1 }

  ioRelayStatusEntry OBJECT-TYPE
      SYNTAX      IoRelayStatusEntry
      MAX-ACCESS  not-accessible
      STATUS      current
      DESCRIPTION
              "An entry in the ioRelayStatusTable"
      INDEX   { ioRelayStatusChannelIndex }
      ::= { ioRelayStatusTable 1 }

  IoRelayStatusEntry ::= 
      SEQUENCE {
        ioRelayStatusChannelIndex          GenericTableIndex,
        ioRelayStatusEnabled          OnOffValue,
        ioRelayStatusDescription          DisplayString,
        ioRelayFunction          INTEGER,
        ioRelayStatusState          INTEGER,
        ioRelayStatusExtensionState          INTEGER
      }

  ioRelayStatusChannelIndex OBJECT-TYPE
      SYNTAX      GenericTableIndex
      MAX-ACCESS  not-accessible
      STATUS      current
      DESCRIPTION
              "Index"
      ::= { ioRelayStatusEntry 1 }

  ioRelayStatusEnabled OBJECT-TYPE
      SYNTAX      OnOffValue
      MAX-ACCESS  read-only
      STATUS      current
      DESCRIPTION
              "Enabled"
      ::= { ioRelayStatusEntry 2 }
      
  ioRelayStatusDescription OBJECT-TYPE
      SYNTAX      DisplayString(SIZE(0..20))
      MAX-ACCESS  read-only
      STATUS      current
      DESCRIPTION
              "Description"
      ::= { ioRelayStatusEntry 3 }
      
  ioRelayFunction OBJECT-TYPE
      SYNTAX      INTEGER {
        none(1),
        kill(2),
        activateOutput(3),
        deactivateOutput(4)
      }
      MAX-ACCESS  read-write
      STATUS      current
      DESCRIPTION
              "kill - Apply configuration changes to this entry"
      ::= { ioRelayStatusEntry 4 }

  ioRelayStatusState OBJECT-TYPE
      SYNTAX      INTEGER {
        inactive(1),
        active(2)
      }
      MAX-ACCESS  read-write
      STATUS      current
      DESCRIPTION
              "Relay State.  ."
      ::= { ioRelayStatusEntry 5 }
	  
  ioRelayStatusExtensionState OBJECT-TYPE
      SYNTAX      INTEGER {
        disable(1),
        enabledDisconnected(2),
        connected(3),
		notAvailable(4)
      }
      MAX-ACCESS  read-only
      STATUS      current
      DESCRIPTION
              "For digital inputs/outputs/relays only."
      ::= { ioRelayStatusEntry 6 }
   -- I/O Relay status ENDS 

   
  -- I/O LineSignal status BEGINS
  ioLineSignalStatusTable OBJECT-TYPE
      SYNTAX      SEQUENCE OF IoLineSignalStatusEntry
      MAX-ACCESS  not-accessible
      STATUS      current
      DESCRIPTION
              "ioLineSignalStatusTable."
      ::= { ioLineSignalStatus 1 }

  ioLineSignalStatusEntry OBJECT-TYPE
      SYNTAX      IoLineSignalStatusEntry
      MAX-ACCESS  not-accessible
      STATUS      current
      DESCRIPTION
              "An entry in the ioLineSignalStatusTable"
      INDEX   { ioLineSignalStatusPortIndex, ioLineSignalStatusSignalIndex  }
      ::= { ioLineSignalStatusTable 1 }

  IoLineSignalStatusEntry ::= 
      SEQUENCE {
        ioLineSignalStatusPortIndex          GenericTableIndex,
        ioLineSignalStatusSignalIndex        INTEGER,
        ioLineSignalStatusEnabled            OnOffValue,
        ioLineSignalStatusDescription        DisplayString,
        ioLineSignalStatusType               INTEGER,
        ioLineSignalFunction                 INTEGER,
        ioLineSignalStatusState              INTEGER,
        ioLineSignalStatusLatchedInputState  INTEGER,
        ioLineSignalStatusInputAlarm         INTEGER,
        ioLineSignalStatusExtensionState     INTEGER

      }

  ioLineSignalStatusPortIndex OBJECT-TYPE
      SYNTAX      GenericTableIndex
      MAX-ACCESS  not-accessible
      STATUS      current
      DESCRIPTION
              "Index"
      ::= { ioLineSignalStatusEntry 1 }

  ioLineSignalStatusSignalIndex OBJECT-TYPE
      SYNTAX      INTEGER {
          dsr(1),
          dcd(2),
          cts(3),
          dtr(4),
          rts(5)
      }
          
      MAX-ACCESS  not-accessible
      STATUS      current
      DESCRIPTION
              "Index"
      ::= { ioLineSignalStatusEntry 2 }
      
  ioLineSignalStatusEnabled OBJECT-TYPE
      SYNTAX      OnOffValue
      MAX-ACCESS  read-only
      STATUS      current
      DESCRIPTION
              "Enabled"
      ::= { ioLineSignalStatusEntry 3 }
      
  ioLineSignalStatusDescription OBJECT-TYPE
      SYNTAX      DisplayString(SIZE(0..20))
      MAX-ACCESS  read-only
      STATUS      current
      DESCRIPTION
              "Description"
      ::= { ioLineSignalStatusEntry 4 }
      
  ioLineSignalStatusType OBJECT-TYPE
      SYNTAX      INTEGER {
        unknown(1),
        input(2),
        output(3)
      }
      MAX-ACCESS  read-only
      STATUS      current
      DESCRIPTION
              "resource type"
      ::= { ioLineSignalStatusEntry 5 }
      
  ioLineSignalFunction OBJECT-TYPE
      SYNTAX      INTEGER {
        none(1),
        kill(2),
        activateOutput(3),
        deactivateOutput(4),
        clearInputLatch(5),
        clearAlarmLatch(6)
      }
      MAX-ACCESS  read-write
      STATUS      current
      DESCRIPTION
              "kill - Apply configuration changes to this entry"
      ::= { ioLineSignalStatusEntry 6 }
  ioLineSignalStatusState OBJECT-TYPE
      SYNTAX      INTEGER {
        inactive(1),
        active(2)
      }
      MAX-ACCESS  read-write
      STATUS      current
      DESCRIPTION
              "LineSignal State.  ."
      ::= { ioLineSignalStatusEntry 7 }
  ioLineSignalStatusLatchedInputState OBJECT-TYPE
      SYNTAX      INTEGER {
        none(1),
        inactiveToActive(2),
        activeToInactive(3)
      }
      MAX-ACCESS  read-only
      STATUS      current
      DESCRIPTION
              "LineSignal State.  ."
      ::= { ioLineSignalStatusEntry 8 }      
  ioLineSignalStatusInputAlarm OBJECT-TYPE
      SYNTAX      INTEGER {
        notTriggered(1),
        triggered(2)
      }
      MAX-ACCESS  read-only
      STATUS      current
      DESCRIPTION
              "LineSignal State.  ."
      ::= { ioLineSignalStatusEntry 9 }

  ioLineSignalStatusExtensionState OBJECT-TYPE
      SYNTAX      INTEGER {
        disable(1),
        enabledDisconnected(2),
        connected(3),
		notAvailable(4)
      }
      MAX-ACCESS  read-only
      STATUS      current
      DESCRIPTION
              "For serial inputs and outputs only."
      ::= { ioLineSignalStatusEntry 10 }      
   -- I/O Line Signal status ENDS 
   
-- I/O Group ENDS

--  ClusteringInfo group. A table of entries, each entry per port.

  clusteringTable OBJECT-TYPE
      SYNTAX      SEQUENCE OF ClusteringEntry
      MAX-ACCESS  not-accessible
      STATUS      current
      DESCRIPTION
              "The Clustering table."
      ::= { clusteringInfo 1 }

  clusteringEntry OBJECT-TYPE
      SYNTAX      ClusteringEntry
      MAX-ACCESS  not-accessible
      STATUS      current
      DESCRIPTION
              "An entry in the clusteringEntry, each relating to a port."
      INDEX   { clusteringIndex }
      ::= { clusteringTable 1 }

  ClusteringEntry ::=
     SEQUENCE {
        clusteringIndex          GenericTableIndex,
        clusteringStatus         ContainerStatus,
        clusteringServerName     DisplayString,
        clusteringSlaveIP        IpAddress,
        clusteringPort           GenericTableIndex,
        clusteringPortName       DisplayString,
        clusteringSlavePort      Integer32,
        clusteringMasterPort     Integer32,
        clusteringProtocol       INTEGER,
        clusteringSlaveIPTunnel  DisplayString
     }

  clusteringIndex OBJECT-TYPE
      SYNTAX      GenericTableIndex
      MAX-ACCESS  not-accessible
      STATUS      current
      DESCRIPTION
              "The table entry number."
      ::= { clusteringEntry 1 }

   clusteringStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { clusteringEntry 2}

   clusteringServerName OBJECT-TYPE
      SYNTAX      DisplayString(SIZE(1..15))
      MAX-ACCESS  read-write
      STATUS      current
      DESCRIPTION
              "The slave server's name."
      ::= { clusteringEntry 3 }
      
   clusteringSlaveIP OBJECT-TYPE
      SYNTAX      IpAddress
      MAX-ACCESS  read-write
      STATUS      current
      DESCRIPTION
              "The remote slave server's IP address."
      ::= { clusteringEntry 4}
            
   clusteringPort OBJECT-TYPE
      SYNTAX      GenericTableIndex
      MAX-ACCESS  read-write
      STATUS      current
      DESCRIPTION
              "The port number on the clustered slave server."
      ::= { clusteringEntry 5}

  clusteringPortName OBJECT-TYPE
      SYNTAX      DisplayString(SIZE(1..54))
      MAX-ACCESS  read-write
      STATUS      current
      DESCRIPTION
              "The slave server's port name."
      ::= { clusteringEntry 6 }
      
   clusteringSlavePort OBJECT-TYPE
      SYNTAX      Integer32(1..65535)
      MAX-ACCESS  read-write
      STATUS      current
      DESCRIPTION
              "The starting TCP port on the slave server."
      ::= { clusteringEntry 7}

   clusteringMasterPort OBJECT-TYPE
      SYNTAX      Integer32(1..65535)
      MAX-ACCESS  read-write
      STATUS      current
      DESCRIPTION
              "The starting TCP port on the master server."
      ::= { clusteringEntry 8}

   clusteringProtocol OBJECT-TYPE
      SYNTAX      INTEGER {
        telnet(1),
        ssh(2),
        notUsed (3)

      }
      MAX-ACCESS  read-write
      STATUS      current
      DESCRIPTION
              "The protocol used to connect between the slave and server."
      ::= { clusteringEntry 9}
  
   clusteringSlaveIPTunnel OBJECT-TYPE
      SYNTAX      DisplayString(SIZE(1..14))
      MAX-ACCESS  read-write
      STATUS      current
      DESCRIPTION
              "The HTTP tunnel associated with the slave IP"
      ::= { clusteringEntry 10}
  
      
-- Dynamic DSN Info
   dynamicDNSStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {dynamicDNSInfo 1}
      
  dynamicDNSEnabled OBJECT-TYPE
      SYNTAX      OnOffValue
      MAX-ACCESS  read-write
      STATUS      current
      DESCRIPTION
              "Enable/disable dynamic DNS."
      ::= { dynamicDNSInfo 2}

  dynamicDNSHostname OBJECT-TYPE
      SYNTAX      DisplayString(SIZE(1..14))
      MAX-ACCESS  read-write
      STATUS      current
      DESCRIPTION
              "Host name."
      ::= { dynamicDNSInfo 3}
      
  dynamicDNSUserName OBJECT-TYPE
      SYNTAX      DisplayString(SIZE(1..16))
      MAX-ACCESS  read-write
      STATUS      current
      DESCRIPTION
              "user name."
      ::= { dynamicDNSInfo 4}
      
  dynamicDNSPassword OBJECT-TYPE
      SYNTAX      DisplayString(SIZE(1..16))
      MAX-ACCESS  read-write
      STATUS      current
      DESCRIPTION
              "Password."
      ::= { dynamicDNSInfo 5}
      
  dynamicDNSSystemType OBJECT-TYPE
      SYNTAX      INTEGER {
        dynamic(1),
        static(2),
        custom(3)
      }
      MAX-ACCESS  read-write
      STATUS      current
      DESCRIPTION
              "System type."
      ::= { dynamicDNSInfo 6}
      
  dynamicDNSWildcard OBJECT-TYPE
      SYNTAX      INTEGER {
        enable(1),
        disable(2),
        nochange(3)
      }
      MAX-ACCESS  read-write
      STATUS      current
      DESCRIPTION
              "wildcard."
      ::= { dynamicDNSInfo 7}
      
  dynamicDNSConnectionMethod OBJECT-TYPE
      SYNTAX      INTEGER {
        http(1),
        httpport8245(2),
        https(3)
      }
      MAX-ACCESS  read-write
      STATUS      current
      DESCRIPTION
              "connection method."
      ::= { dynamicDNSInfo 8}
      
  dynamicDNSSSLVerifyPeerCertificate  OBJECT-TYPE
      SYNTAX   OnOffValue
      MAX-ACCESS    read-write
      STATUS        current
      DESCRIPTION
                "Enable this option when you want the Validation Criteria
                 to match the Peer Certificate for authentication to pass.
                 If you enable this option, you need to download an  
                 SSL/TLS certificate authority (CA) list file to the 
                 Device Server. Any values that are entered in the validation
                 criteria must match the peer certificate for an SSL connection;
                 any fields left blank will not be validated against the peer 
                 certificate."
      ::= {dynamicDNSInfo 9}

  dynamicDNSSSLCountry    OBJECT-TYPE
      SYNTAX      DisplayString(SIZE(0..2))
      MAX-ACCESS    read-write
      STATUS        current
      DESCRIPTION
                "A two character country code; for example, US."
      ::= {dynamicDNSInfo 10}

  dynamicDNSSSLStateProv    OBJECT-TYPE
      SYNTAX      DisplayString(SIZE(0..128))
      MAX-ACCESS    read-write
      STATUS        current
      DESCRIPTION
                "Up to a 128 character entry for the state/province;
                 for example, IL."
      ::= {dynamicDNSInfo 11}

  dynamicDNSSSLLocality    OBJECT-TYPE
      SYNTAX      DisplayString(SIZE(0..128))
      MAX-ACCESS    read-write
      STATUS        current
      DESCRIPTION
                "Up to a 128 character entry for the location; 
                 for example, a city."
      ::= {dynamicDNSInfo 12}

  dynamicDNSSSLOrganisation    OBJECT-TYPE
      SYNTAX      DisplayString(SIZE(0..64))
      MAX-ACCESS    read-write
      STATUS        current
      DESCRIPTION
                "Up to a 64 character entry for the organization; 
                 for example, Accounting."
      ::= {dynamicDNSInfo 13}

  dynamicDNSSSLOrganisationUnit    OBJECT-TYPE
      SYNTAX      DisplayString(SIZE(0..64))
      MAX-ACCESS    read-write
      STATUS        current
      DESCRIPTION
                "Up to a 64 character entry for the unit in the 
                 organization; for example, Payroll."
      ::= {dynamicDNSInfo 14}

  dynamicDNSSSLCommonName    OBJECT-TYPE
      SYNTAX      DisplayString(SIZE(0..64))
      MAX-ACCESS    read-write
      STATUS        current
      DESCRIPTION
                "Up to a 64 character entry for common name; for example,
                 the host name or fully qualified domain name."
      ::= {dynamicDNSInfo 15}

  dynamicDNSSSLEmail    OBJECT-TYPE
      SYNTAX      DisplayString(SIZE(0..128))
      MAX-ACCESS    read-write
      STATUS        current
      DESCRIPTION
                "Up to a 64 character entry for an email address; 
                 for example, acct@anycompany.com."
      ::= {dynamicDNSInfo 16}

      dynamicDNSStatusString OBJECT-TYPE
      SYNTAX      OCTET STRING (SIZE(0..1024))
      MAX-ACCESS  read-only
      STATUS      current
      DESCRIPTION
              "Dynamic DNS statistics"
      ::= {dynamicDNSInfo 17}
-- Dynamic DND SSL Cipher Table

  dynamicDNSSSLCipherTable OBJECT-TYPE
      SYNTAX      SEQUENCE OF DynamicDNSSSLCipherEntry
      MAX-ACCESS  not-accessible
      STATUS      current
      DESCRIPTION
              "SSL CIpher."
      ::= {dynamicDNSInfo 18}

  dynamicDNSSSLCipherEntry OBJECT-TYPE
      SYNTAX      DynamicDNSSSLCipherEntry
      MAX-ACCESS  not-accessible
      STATUS      current
      DESCRIPTION
              "An entry in the dynamicDNSSSLCipherTable, each relating to a cipher entry."
      INDEX   { dynamicDNSSSLCipherPriority }
      ::= { dynamicDNSSSLCipherTable 1 }

  DynamicDNSSSLCipherEntry ::=
      SEQUENCE {
  dynamicDNSSSLCipherPriority        Integer32,
  dynamicDNSSSLCipherStatus        ContainerStatus,
  dynamicDNSSSLCipherEncryption        INTEGER,
  dynamicDNSSSLCipherKeySizeMin        INTEGER,
  dynamicDNSSSLCipherKeySizeMax        INTEGER,
  dynamicDNSSSLCipherKeyExchange        INTEGER,
  dynamicDNSSSLCipherHMAC        INTEGER
      }

  dynamicDNSSSLCipherPriority OBJECT-TYPE
      SYNTAX      Integer32(1..5)
      MAX-ACCESS  not-accessible
      STATUS      current
      DESCRIPTION
              "The cipher priority. 1- highest 5 - lowest."
      ::= { dynamicDNSSSLCipherEntry 1 }

  dynamicDNSSSLCipherStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { dynamicDNSSSLCipherEntry 2 }

  dynamicDNSSSLCipherEncryption OBJECT-TYPE
      SYNTAX      INTEGER {
        none(1),
        any(2),
        aes(3),
        tripledes(4),
        des(5),
        arctwo(6),
        arcfour(7)
      }
      MAX-ACCESS  read-write
      STATUS      current
      DESCRIPTION
              "SSL Encryption. None is not allowed for priority 1.
               Any will use the first encryption format that can be 
               negotiated. The default is any."
      ::= { dynamicDNSSSLCipherEntry 3 }

  dynamicDNSSSLCipherKeySizeMin OBJECT-TYPE
      SYNTAX      INTEGER {
        min40(1),
        min56(2),
        min64(3),
        min128(4),
        min168(5),
        min256(6)
      }
      MAX-ACCESS  read-write
      STATUS      current
      DESCRIPTION
              "The minimum key size value that will be used for 
               the specified encryption type. The default is 40."
      ::= { dynamicDNSSSLCipherEntry 4 }

  dynamicDNSSSLCipherKeySizeMax OBJECT-TYPE
      SYNTAX      INTEGER {
        max40(1),
        max56(2),
        max64(3),
        max128(4),
        max168(5),
        max256(6)
      }
      MAX-ACCESS  read-write
      STATUS      current
      DESCRIPTION
              "The maximum key size value that will be used for the
               specified encryption type. The default is 256."
      ::= { dynamicDNSSSLCipherEntry 5 }

  dynamicDNSSSLCipherKeyExchange OBJECT-TYPE
      SYNTAX      INTEGER {
        any(1),
        rsa(2),
        edhrsa(3),
        edhdss(4),
        adh(5) 
      }
      MAX-ACCESS  read-write
      STATUS      current
      DESCRIPTION
              "The type of key to exchange for the encryption format:
               Any-Any key exchange that is valid is used (this does 
                   not, however, include ADH keys).
               RSA-This is an RSA key exchange using an RSA key and 
                   certificate.
               EDHRSA-This is an EDH key exchange using an RSA key 
                   and certificate.
               EDHDSS-This is an EDH key exchange using a DSA key
                   and certificate.
               ADH-This is an anonymous key exchange which does not 
                   require a private key or certificate. Choose this 
                   key if you do not want to authenticate the peer device, 
                   but you want the data encrypted on the SSL/TLS connection.
               The default is Any."
      ::= { dynamicDNSSSLCipherEntry 6 }

  dynamicDNSSSLCipherHMAC OBJECT-TYPE
      SYNTAX      INTEGER {
        any(1),
        sha(2),
        md5(3)
      }
      MAX-ACCESS  read-write
      STATUS      current
      DESCRIPTION
              "Select the key-hashing for message authentication method 
               for your encryption type: Any, MD5, or SHA1.
               The default is Any."
      ::= { dynamicDNSSSLCipherEntry 7 }

        
-- Dynamic DNS Stats Info


-- PCI Info

 pciCardInfo       OBJECT IDENTIFIER ::= { pciInfo 1 }

  pciWwanInfo      OBJECT IDENTIFIER ::= { pciInfo 2 }
  pciFiberLanInfo  OBJECT IDENTIFIER ::= { pciInfo 3 }
  pciUsbInfo       OBJECT IDENTIFIER ::= { pciInfo 4 }
 
 pciCardStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {pciCardInfo 1}
      
 pciCardType OBJECT-TYPE
      SYNTAX INTEGER {
         none(1),
         pciModem(2)
         ,
         wirelessWan(3),
         fiberOpticLan(4),
         usb(5)
         }
      MAX-ACCESS  read-only
      STATUS      current
      DESCRIPTION
              "PCI Card Type"
      ::= { pciCardInfo 2}
 
  wwanCardStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {pciWwanInfo 1}
      
      wwanCardType OBJECT-TYPE
      SYNTAX INTEGER {
         sierra(1),
         sonyEricsson(2),
         otherUseStandardDriver(3),
         otherUseCustomDriver(4),
         sierraWirelessAirCard881(5),
         sonyEricssonPC300(6)
         }
      MAX-ACCESS  read-write
      STATUS      current
      DESCRIPTION
              "Wireless Wan Card Type"
      ::= { pciWwanInfo 2 }
      
 wwanAPN OBJECT-TYPE
      SYNTAX      DisplayString(SIZE(0..60))
      MAX-ACCESS  read-write
      STATUS      current
      DESCRIPTION
              "Specify the APN required by your internet provider to 
               access their network. See the Internet provider 
               documentation for more information. "
      ::= { pciWwanInfo 3 }
      
 wwanUserName OBJECT-TYPE
      SYNTAX      DisplayString(SIZE(0..254))
      MAX-ACCESS  read-write
      STATUS      current
      DESCRIPTION
              "Specify the name required by your Internet provider 
               to access their network."
      ::= { pciWwanInfo 4 }

 wwanPhoneNumer OBJECT-TYPE
      SYNTAX      DisplayString(SIZE(0..31))
      MAX-ACCESS  read-write
      STATUS      current
      DESCRIPTION
              "Specify the phone number provided by your service 
               provider to access their wireless network. 
               Probably similar to *99***1#"
      ::= { pciWwanInfo 5}
      
 wwanInitString OBJECT-TYPE
      SYNTAX      DisplayString(SIZE(0..60))
      MAX-ACCESS  read-write
      STATUS      current
      DESCRIPTION
              "Specify the initialization string required by your 
               Internet service provider for your wireless WAN card."
      ::= { pciWwanInfo 6}
      
  wwanNetworkRegistration OBJECT-TYPE
      SYNTAX      Integer32(0..5)
      MAX-ACCESS  read-only
      STATUS      current
      DESCRIPTION
              "Network Registration.
	      Possible Values
	      0 - Not Registered. Not searching for a network,
	      1 - Registered. Home Network,
	      2 - Not Registered. Searching for a network,
	      3 - Registration Denied
	      4 - Unknown,
	      5 - Registered. Roaming"
      ::= { pciWwanInfo 7}
      
  wwanSignalStrength OBJECT-TYPE
      SYNTAX      Integer32(0..4294967)
      MAX-ACCESS  read-only
      STATUS      current
      DESCRIPTION
              "Signal Strength"
      ::= { pciWwanInfo 8}

  pciFiberLanStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {pciFiberLanInfo 1}
      
      pciFiberLanType OBJECT-TYPE
      SYNTAX INTEGER {
         kTIKG500F(1),
         transitionNetworksNFXSC502(2)
         }
      MAX-ACCESS  read-write
      STATUS      current
      DESCRIPTION
              "PCI Fiber LAN Card Type"
      ::= { pciFiberLanInfo 2}

  usbStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {pciUsbInfo 1}
      
 usbAPN OBJECT-TYPE
      SYNTAX      DisplayString(SIZE(0..60))
      MAX-ACCESS  read-write
      STATUS      current
      DESCRIPTION
              "Specify the APN required by your internet provider to 
               access their network. See the Internet provider 
               documentation for more information. "
      ::= { pciUsbInfo 2 }
      
 usbUserName OBJECT-TYPE
      SYNTAX      DisplayString(SIZE(0..254))
      MAX-ACCESS  read-write
      STATUS      current
      DESCRIPTION
              "Specify the name required by your Internet provider 
               to access their network."
      ::= { pciUsbInfo 3 }

 usbPhoneNumer OBJECT-TYPE
      SYNTAX      DisplayString(SIZE(0..31))
      MAX-ACCESS  read-write
      STATUS      current
      DESCRIPTION
              "Specify the phone number provided by your service 
               provider to access their wireless network. 
               Probably similar to *99***1#"
      ::= { pciUsbInfo 4}
      
 usbInitString OBJECT-TYPE
      SYNTAX      DisplayString(SIZE(0..60))
      MAX-ACCESS  read-write
      STATUS      current
      DESCRIPTION
              "Specify the initialization string required by your 
               Internet service provider for your USB device."
      ::= { pciUsbInfo 5}
      
 usbPin OBJECT-TYPE
      SYNTAX      DisplayString(SIZE(0..8))
      MAX-ACCESS  read-write
      STATUS      current
      DESCRIPTION
              "Specify the PIN required for your USB device."
      ::= { pciUsbInfo 6}
      

 -- VModem phone Table

  vmodemPhoneInfoTable OBJECT-TYPE
      SYNTAX      SEQUENCE OF VmodemPhoneInfoEntry
      MAX-ACCESS  not-accessible
      STATUS      current
      DESCRIPTION
              "The vmodem phone  info table."
      ::= { vmodemPhoneInfo 1 }

  vmodemPhoneInfoEntry OBJECT-TYPE
      SYNTAX      VmodemPhoneInfoEntry
      MAX-ACCESS  not-accessible
      STATUS      current
      DESCRIPTION
              "An entry in the vmodemPhoneInfoTable, each relating to a host."
      INDEX   { vmodemPhoneIndex }
      ::= { vmodemPhoneInfoTable 1 }

  VmodemPhoneInfoEntry ::=
      SEQUENCE {
        vmodemPhoneIndex      	GenericTableIndex,
        vmodemPhoneStatus    		ContainerStatus,
        vmodemPhone            	DisplayString,
        vmodemPhoneIP          	Ipv4v6Address,
        vmodemPhonePort        	Integer32,
        vmodemPhoneTunnelName  	DisplayString,
        vmodemPhoneHostName		DisplayString
      }

  vmodemPhoneIndex OBJECT-TYPE
      SYNTAX      GenericTableIndex
      MAX-ACCESS  not-accessible
      STATUS      current
      DESCRIPTION
              "The table entry number for this vmodem phone table"
      ::= { vmodemPhoneInfoEntry 1 }

  vmodemPhoneStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { vmodemPhoneInfoEntry 2 }

  vmodemPhone OBJECT-TYPE
      SYNTAX      DisplayString(SIZE(0..31))
      MAX-ACCESS  read-write
      STATUS      current
      DESCRIPTION
              "The modem name used for this modem entry. If blank, this entry
               is currently unused."
      ::= { vmodemPhoneInfoEntry 3 }

  vmodemPhoneIP OBJECT-TYPE
      SYNTAX      Ipv4v6Address
      MAX-ACCESS  read-write
      STATUS      current
      DESCRIPTION
              "The IP address corresponding to a phone number. If the IP address
               is blank, then the Host IP address will be used"
      ::= { vmodemPhoneInfoEntry 4 }


  vmodemPhonePort OBJECT-TYPE
      SYNTAX      Integer32(0..65535)
      MAX-ACCESS  read-write
      STATUS      current
      DESCRIPTION
              "TCP port number corresponding to a phone number."
      ::= { vmodemPhoneInfoEntry 5 }

  vmodemPhoneTunnelName OBJECT-TYPE
      SYNTAX      DisplayString(SIZE(0..14))
      MAX-ACCESS  read-write
      STATUS      current
      DESCRIPTION
              "The name of the HTTP tunnel associated with this service."
      ::= { vmodemPhoneInfoEntry 6 }
  
  vmodemPhoneHostName OBJECT-TYPE
      SYNTAX      DisplayString (SIZE(0..14))
      MAX-ACCESS  read-write
      STATUS      current
      DESCRIPTION
              "The name of a configured host that will correspond to the phone
              number."
      ::= { vmodemPhoneInfoEntry 7}

  
--  ipsecInfo group. A table of entries, each entry per IPsec tunnel.

  ipsecTable OBJECT-TYPE
      SYNTAX      SEQUENCE OF IpsecEntry
      MAX-ACCESS  not-accessible
      STATUS      current
      DESCRIPTION
              "The IPsec table."
      ::= { ipsecInfo 1 }

  ipsecEntry OBJECT-TYPE
      SYNTAX      IpsecEntry
      MAX-ACCESS  not-accessible
      STATUS      current
      DESCRIPTION
              "An entry in the ipsecEntry, each relating to a IPsec tunnel."
      INDEX   { ipsecIndex }
      ::= { ipsecTable 1 }

  IpsecEntry ::=
      SEQUENCE {
        ipsecIndex              GenericTableIndex,
        ipsecStatus            ContainerStatus,
        ipsecName              DisplayString,
        ipsecAuthMethod              INTEGER,
        ipsecSecret              DisplayString,
        ipsecLocalDevice              INTEGER,
        ipsecBootaction              INTEGER,     
        ipsecLocalIpAddress              DisplayString,     
        ipsecLocalExternalIpAddress              DisplayString,  
        ipsecLocalNextHop            Ipv4v6Address,
        ipsecLocalHostNetwork            Ipv4v6Address,
        ipsecLocalNetmaskBit              Integer32,     
        ipsecRemoteIpAddress              DisplayString,     
        ipsecRemoteExternalIpAddress              DisplayString,  
        ipsecRemoteNextHop            Ipv4v6Address,
        ipsecRemoteHostNetwork            Ipv4v6Address,
        ipsecRemoteNetmaskBit             Integer32,
        ipsecRemoteValCritCountry        	DisplayString,
        ipsecRemoteValCritStateProv        	DisplayString,
        ipsecRemoteValCritLocality        	DisplayString,
        ipsecRemoteValCritOrganisation        	DisplayString, 	     
        ipsecRemoteValCritOrganisationUnit        	DisplayString,
        ipsecRemoteValCritCommonName        	DisplayString,
        ipsecRemoteValCritEmail         	DisplayString  	
            }

  ipsecIndex OBJECT-TYPE
      SYNTAX      GenericTableIndex
      MAX-ACCESS  not-accessible
      STATUS      current
      DESCRIPTION
              "The table entry number for this IPsec tunnel."
      ::= { ipsecEntry 1 }

   ipsecStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ipsecEntry 2}

  ipsecName OBJECT-TYPE
      SYNTAX      DisplayString(SIZE(0..16))
      MAX-ACCESS  read-write
      STATUS      current
      DESCRIPTION
              "The IPsec tunnel name.
               To delete an IPsec, set this field to blank.
               If blank, this entry is currently unused."
      ::= { ipsecEntry 3 }

 ipsecAuthMethod OBJECT-TYPE
      SYNTAX      INTEGER {
        sharedSecret(0),
        rsaSignature(2),
        x509Certificate(3)
      }
      MAX-ACCESS  read-write
      STATUS      current
      DESCRIPTION
              "The type of authentication Method that the IPsec tunnel will use"
      ::= {ipsecEntry 4 }
      
 ipsecSecret OBJECT-TYPE
      SYNTAX      DisplayString(SIZE(0..16))
      MAX-ACCESS  read-write
      STATUS      current
      DESCRIPTION
              "The IPsec tunnel secret. This applies to all IPsec and
               and L2TP/IPsec tunnels"
      ::= { ipsecEntry 5 }

 ipsecLocalDevice OBJECT-TYPE
      SYNTAX      INTEGER {
        left(1),
        right(2)
      }
      MAX-ACCESS  read-write
      STATUS      current
      DESCRIPTION
              "Define local device (the Device Server) either in left or right"
      ::= {ipsecEntry 6 }
      
  ipsecBootaction OBJECT-TYPE
      SYNTAX      INTEGER {
        start(1),
        add(2),
        ignore(3)
      }
      MAX-ACCESS  read-write
      STATUS      current
      DESCRIPTION
              "Select one of the boot action from: start, add or ignore."
      ::= {ipsecEntry 7 }   
      
  ipsecLocalIpAddress OBJECT-TYPE
      SYNTAX      DisplayString(SIZE(0..126))
      MAX-ACCESS  read-write
      STATUS      current
      DESCRIPTION
              "IPv4/IPv6 or FQDN(Fully Qualified Domain Name)"
      ::= { ipsecEntry 8}

  ipsecLocalExternalIpAddress OBJECT-TYPE
      SYNTAX      DisplayString(SIZE(0..126))
      MAX-ACCESS  read-write
      STATUS      current
      DESCRIPTION
              "External/unique IPv4/IPv6 address or Full Qualified Domain Name(FQDN) when using NAT_T through 
              a router/firewall. Only Available if Nat-T is on."
      ::= { ipsecEntry 9}

  ipsecLocalNextHop OBJECT-TYPE
      SYNTAX      Ipv4v6Address
      MAX-ACCESS  read-write
      STATUS      current
      DESCRIPTION
              "The IP address of the router/gateway to send this packet to. Must be on the same subnet as the IP Address. 
              Leave blank if using the default gateway configured in the IOLAN's->Network->Gateways settings."
      ::= { ipsecEntry 10 }
      
  ipsecLocalHostNetwork OBJECT-TYPE
      SYNTAX      Ipv4v6Address
      MAX-ACCESS  read-write
      STATUS      current
      DESCRIPTION
              "The network we are trying to create a VPN connection for. Leave blank when creating 
              a host to host VPN connection."
      ::= { ipsecEntry 11 }

  ipsecLocalNetmaskBit OBJECT-TYPE
      SYNTAX      Integer32(0..128)
      MAX-ACCESS  read-write
      STATUS      current
      DESCRIPTION
              "If the local host/network address is IPv4,
               then the Subnet/Prefix Bits range is 0-32. If the IP address
               is IPv6, then the Subnet/Prefix Bits range is 0-128."
      ::= {  ipsecEntry 12 }
      
  ipsecRemoteIpAddress OBJECT-TYPE
      SYNTAX      DisplayString(SIZE(0..126))
      MAX-ACCESS  read-write
      STATUS      current
      DESCRIPTION
              "IPv4/IPv6 or FQDN(Fully Qualified Domain Name)"
      ::= { ipsecEntry 13}

  ipsecRemoteExternalIpAddress OBJECT-TYPE
      SYNTAX      DisplayString(SIZE(0..126))
      MAX-ACCESS  read-write
      STATUS      current
      DESCRIPTION
              "External/unique IPv4/IPv6 address or Full Qualified Domain Name(FQDN) when using NAT_T throught 
              a router/firewall. Only Available if Nat-T is on."
      ::= { ipsecEntry 14}

  ipsecRemoteNextHop OBJECT-TYPE
      SYNTAX      Ipv4v6Address
      MAX-ACCESS  read-write
      STATUS      current
      DESCRIPTION
              "The IP address of the router/gateway to send this packet to. Must be on the same subnet as the IP Address. 
              Leave blank if using the default gateway configured in the IOLAN's->Network->Gateways settings."
      ::= { ipsecEntry 15 }
      
  ipsecRemoteHostNetwork OBJECT-TYPE
      SYNTAX      Ipv4v6Address
      MAX-ACCESS  read-write
      STATUS      current
      DESCRIPTION
              "The host/network we are trying to create a VPN connection for. Leave blank when creating 
              a host to host VPN connection."
      ::= { ipsecEntry 16 }

ipsecRemoteNetmaskBit OBJECT-TYPE
      SYNTAX      Integer32(0..128)
      MAX-ACCESS  read-write
      STATUS      current
      DESCRIPTION
              "If the remote host/network address is IPv4,
               then the Subnet/Prefix Bits range is 0-32. If the IP address
               is IPv6, then the Subnet/Prefix Bits range is 0-128."
      ::= {  ipsecEntry 17 }     

 ipsecRemoteValCritCountry    OBJECT-TYPE
      SYNTAX      DisplayString(SIZE(0..2))
      MAX-ACCESS    read-write
      STATUS        current
      DESCRIPTION
                "A two character country code; for example, US."
    ::= {  ipsecEntry 18 }   

  ipsecRemoteValCritStateProv    OBJECT-TYPE
      SYNTAX      DisplayString(SIZE(0..128))
      MAX-ACCESS    read-write
      STATUS        current
      DESCRIPTION
                "Up to a 128 character entry for the state/province;
                 for example, IL."
     ::= {  ipsecEntry 19 }   

  ipsecRemoteValCritLocality    OBJECT-TYPE
      SYNTAX      DisplayString(SIZE(0..128))
      MAX-ACCESS    read-write
      STATUS        current
      DESCRIPTION
                "Up to a 128 character entry for the location; 
                 for example, a city."
     ::= {  ipsecEntry 20 }   

  ipsecRemoteValCritOrganisation    OBJECT-TYPE
      SYNTAX      DisplayString(SIZE(0..64))
      MAX-ACCESS    read-write
      STATUS        current
      DESCRIPTION
                "Up to a 64 character entry for the organization; 
                 for example, Accounting."
   ::= {  ipsecEntry 21 }   

  ipsecRemoteValCritOrganisationUnit    OBJECT-TYPE
      SYNTAX      DisplayString(SIZE(0..64))
      MAX-ACCESS    read-write
      STATUS        current
      DESCRIPTION
                "Up to a 64 character entry for the unit in the 
                 organization; for example, Payroll."
   ::= {  ipsecEntry 22 }   

  ipsecRemoteValCritCommonName    OBJECT-TYPE
      SYNTAX      DisplayString(SIZE(0..64))
      MAX-ACCESS    read-write
      STATUS        current
      DESCRIPTION
                "Up to a 64 character entry for common name; for example,
                 the host name or fully qualified domain name."
    ::= {  ipsecEntry 23 }   

  ipsecRemoteValCritEmail    OBJECT-TYPE
      SYNTAX      DisplayString(SIZE(0..128))
      MAX-ACCESS    read-write
      STATUS        current
      DESCRIPTION
                "Up to a 64 character entry for an email address; 
                 for example, acct@anycompany.com."
   ::= {  ipsecEntry 24 }

-- IPv6 Info

  ipv6ServicesInfo          OBJECT IDENTIFIER ::= { ipv6Info 1 }

  ipv6serviceStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {ipv6ServicesInfo 1}

  serviceAutoDiscovery1 OBJECT-TYPE
      SYNTAX      OnOffValue
      MAX-ACCESS  read-write
      STATUS      current
      DESCRIPTION
              "(Ethernet 1) When on, the Device Server will send out a Router Solicitation 
               message. If a Router Advertisement message is received, the 
               Device Server will configure the IPv6 address(es) and configuration 
               parameters based on the information contained in the advertisement. 
               If no Router Advertisement message is received, the Device Server 
               will attempt to connect to a DHCPv6 server to obtain IPv6 addresses 
               and other configuration parameters. Default on."
      ::= { ipv6ServicesInfo 2 }

  serviceDHCPv61 OBJECT-TYPE
      SYNTAX      OnOffValue
      MAX-ACCESS  read-write
      STATUS      current
      DESCRIPTION
              "(Ethernet 1) When on, requests IPv6 address(es) and configuration 
               information from the DHCPv6 server. Default off."
      ::= { ipv6ServicesInfo 3 }
      
  serviceRouterAdvertisement1 OBJECT-TYPE
      SYNTAX      OnOffValue
      MAX-ACCESS  read-write
      STATUS      current
      DESCRIPTION
              "(Ethernet 1) When on, the Device Server will periodically send IPv6 
               Router Advertisement messages and respond to Router Solicitation messages. 
               The Router Advertisement message can be configured to contain 
               any of the following information:
               o DHCPv6-Use the DHCPv6 server to obtain additional IPv6 
                 address(es) and configuration parameters.
               o DHCPv6 Configuration Options-Use DHCPv6 server to obtain 
                 additional configuration parameters.
               o Network Prefixes-Advertise the selected custom configured 
                 network prefixes. 
               Default is off."
      ::= { ipv6ServicesInfo 4 }

  serviceRouterAdvertisementDHCP1 OBJECT-TYPE
      SYNTAX      OnOffValue
      MAX-ACCESS  read-write
      STATUS      current
      DESCRIPTION
              "(Ethernet 1) When on, the Router Advertisement message indicates to use the DHCPv6 
               server for obtaining additional IPv6 addresses and configuration parameters.
               Default is off."
      ::= { ipv6ServicesInfo 5 }

  serviceRouterAdvertisementOther1 OBJECT-TYPE
      SYNTAX      OnOffValue
      MAX-ACCESS  read-write
      STATUS      current
      DESCRIPTION
              "(Ethernet 1) When on, the Router Advertisement message indicates to use 
               the DHCPv6 server to obtain additional configuration parameters. 
               Default is off."
      ::= { ipv6ServicesInfo 6 }

  serviceAutoDiscovery2 OBJECT-TYPE
      SYNTAX      OnOffValue
      MAX-ACCESS  read-write
      STATUS      current
      DESCRIPTION
              "(Ethernet 2) When on, the Device Server will send out a Router Solicitation 
               message. If a Router Advertisement message is received, the 
               Device Server will configure the IPv6 address(es) and configuration 
               parameters based on the information contained in the advertisement. 
               If no Router Advertisement message is received, the Device Server 
               will attempt to connect to a DHCPv6 server to obtain IPv6 addresses 
               and other configuration parameters. Default on. "
      ::= { ipv6ServicesInfo 7 }

  serviceDHCPv62 OBJECT-TYPE
      SYNTAX      OnOffValue
      MAX-ACCESS  read-write
      STATUS      current
      DESCRIPTION
              "(Ethernet 2) When on, requests IPv6 address(es) and configuration 
               information from the DHCPv6 server. Default off."
      ::= { ipv6ServicesInfo 8 }
      
  serviceRouterAdvertisement2 OBJECT-TYPE
      SYNTAX      OnOffValue
      MAX-ACCESS  read-write
      STATUS      current
      DESCRIPTION
              "(Ethernet 2) When on, the Device Server will periodically send IPv6 
               Router Advertisement messages and respond to Router Solicitation messages. 
               The Router Advertisement message can be configured to contain 
               any of the following information:
               o DHCPv6-Use the DHCPv6 server to obtain additional IPv6 
                 address(es) and configuration parameters.
               o DHCPv6 Configuration Options-Use DHCPv6 server to obtain 
                 additional configuration parameters.
               o Network Prefixes-Advertise the selected custom configured 
                 network prefixes. 
               Default is off."
      ::= { ipv6ServicesInfo 9 }

  serviceRouterAdvertisementDHCP2 OBJECT-TYPE
      SYNTAX      OnOffValue
      MAX-ACCESS  read-write
      STATUS      current
      DESCRIPTION
              "(Ethernet 2) When on, the Router Advertisement message indicates to use the DHCPv6 
               server for obtaining additional IPv6 addresses and configuration parameters.
               Default is off."
      ::= { ipv6ServicesInfo 10 }

  serviceRouterAdvertisementOther2 OBJECT-TYPE
      SYNTAX      OnOffValue
      MAX-ACCESS  read-write
      STATUS      current
      DESCRIPTION
              "(Ethernet 2) When on, the Router Advertisement message indicates to use 
               the DHCPv6 server to obtain additional configuration parameters. 
               Default is off."
      ::= { ipv6ServicesInfo 11 }

  serviceDHCPv6IPAddresses OBJECT-TYPE
      SYNTAX      OnOffValue
      MAX-ACCESS  read-write
      STATUS      current
      DESCRIPTION
              "When on, the Device Server will accept IPv6 address(es) 
               from the DHCPv6 server."
      ::= { ipv6ServicesInfo 12 }
      
  serviceDHCPv6NetworkPrefix OBJECT-TYPE
      SYNTAX      OnOffValue
      MAX-ACCESS  read-write
      STATUS      current
      DESCRIPTION
              "When on, the Device Server will accept the network prefix 
               from the DHCPv6 server."
      ::= { ipv6ServicesInfo 13 }
      
  serviceAutoDiscovery3 OBJECT-TYPE
      SYNTAX      OnOffValue
      MAX-ACCESS  read-write
      STATUS      current
      DESCRIPTION
              "(Ethernet 3) When on, the Device Server will send out a Router Solicitation 
               message. If a Router Advertisement message is received, the 
               Device Server will configure the IPv6 address(es) and configuration 
               parameters based on the information contained in the advertisement. 
               If no Router Advertisement message is received, the Device Server 
               will attempt to connect to a DHCPv6 server to obtain IPv6 addresses 
               and other configuration parameters. Default on. "
      ::= { ipv6ServicesInfo 14 }

  serviceDHCPv63 OBJECT-TYPE
      SYNTAX      OnOffValue
      MAX-ACCESS  read-write
      STATUS      current
      DESCRIPTION
              "(Ethernet 3) When on, requests IPv6 address(es) and configuration 
               information from the DHCPv6 server. Default off."
      ::= { ipv6ServicesInfo 15 }
      
  serviceRouterAdvertisement3 OBJECT-TYPE
      SYNTAX      OnOffValue
      MAX-ACCESS  read-write
      STATUS      current
      DESCRIPTION
              "(Ethernet 3) When on, the Device Server will periodically send IPv6 
               Router Advertisement messages and respond to Router Solicitation messages. 
               The Router Advertisement message can be configured to contain 
               any of the following information:
               o DHCPv6-Use the DHCPv6 server to obtain additional IPv6 
                 address(es) and configuration parameters.
               o DHCPv6 Configuration Options-Use DHCPv6 server to obtain 
                 additional configuration parameters.
               o Network Prefixes-Advertise the selected custom configured 
                 network prefixes. 
               Default is off."
      ::= { ipv6ServicesInfo 16 }

  serviceRouterAdvertisementDHCP3 OBJECT-TYPE
      SYNTAX      OnOffValue
      MAX-ACCESS  read-write
      STATUS      current
      DESCRIPTION
              "(Ethernet 3) When on, the Router Advertisement message indicates to use the DHCPv6 
               server for obtaining additional IPv6 addresses and configuration parameters.
               Default is off."
      ::= { ipv6ServicesInfo 10 }

  serviceRouterAdvertisementOther3 OBJECT-TYPE
      SYNTAX      OnOffValue
      MAX-ACCESS  read-write
      STATUS      current
      DESCRIPTION
              "(Ethernet 3) When on, the Router Advertisement message indicates to use 
               the DHCPv6 server to obtain additional configuration parameters. 
               Default is off."
      ::= { ipv6ServicesInfo 11 }

  -- IPv6 Address Table
  	  
  ipv6AddressEth1Table OBJECT-TYPE
      SYNTAX      SEQUENCE OF Ipv6AddressEth1Entry
      MAX-ACCESS  not-accessible
      STATUS      current
      DESCRIPTION
              "Ethernet 1 IPv6 custom address table."
      ::= { ipv6Info 2 }
      
  ipv6AddressEth1Entry OBJECT-TYPE
      SYNTAX      Ipv6AddressEth1Entry
      MAX-ACCESS  not-accessible
      STATUS      current
      DESCRIPTION
              "Ethernet 1 IPv6 custom entry."
      INDEX   { ipv6AddressEth1Index }
      ::= { ipv6AddressEth1Table 1 }
      
      
  Ipv6AddressEth1Entry ::=
      SEQUENCE {
        ipv6AddressEth1Index         	GenericTableIndex,
        ipv6AddressEth1Status        	ContainerStatus,
        ipv6AddressEth1Addr          	Ipv4v6Address,
        ipv6AddressEth1PrefixBits    	Integer32,
		ipv6AddressEth1Auto				OnOffValue,
		ipv6AddressEth1SendAdvertise	OnOffValue
      }
      
  ipv6AddressEth1Index OBJECT-TYPE
      SYNTAX      GenericTableIndex
      MAX-ACCESS  not-accessible
      STATUS      current
      DESCRIPTION
              "Ethernet 1 custom IPv6 address index."
      ::= { ipv6AddressEth1Entry 1 }
      
  ipv6AddressEth1Status OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ipv6AddressEth1Entry 2 }
      
  ipv6AddressEth1Addr OBJECT-TYPE
      SYNTAX      Ipv4v6Address
      MAX-ACCESS  read-write
      STATUS      current
      DESCRIPTION
              "(Ethernet 1) Either enter a network prefix that the Device 
               Server will use to derive an IPv6 address using the Device 
               Server's MAC address (must turn ipv6AddressAuto1 on) 
               or enter a specific IPv6 address."
      ::= { ipv6AddressEth1Entry 3 }
      
  ipv6AddressEth1PrefixBits OBJECT-TYPE
      SYNTAX      Integer32(0..128)
      MAX-ACCESS  read-write
      STATUS      current
      DESCRIPTION
              "(Ethernet 1) The IPv6 prefix bits of either the network or
               IPv6 address."
      ::= { ipv6AddressEth1Entry 4 }
      
  ipv6AddressEth1Auto  OBJECT-TYPE
      SYNTAX   OnOffValue
      MAX-ACCESS    read-write
      STATUS        current
      DESCRIPTION
                "(Ethernet 1) When on, the Device Server will derive 
                 an IPv6 address from the entered network prefix and the 
                 Device Server's MAC address."
      ::= {ipv6AddressEth1Entry 5}
	  
  ipv6AddressEth1SendAdvertise  OBJECT-TYPE
      SYNTAX   OnOffValue
      MAX-ACCESS    read-write
      STATUS        current
      DESCRIPTION
                "(Ethernet 1) When on, the Device Server will include
                 the IPv6 address in router advertisements."
      ::= {ipv6AddressEth1Entry 6}
  
-- ETH 2
  ipv6AddressEth2Table OBJECT-TYPE
      SYNTAX      SEQUENCE OF Ipv6AddressEth2Entry
      MAX-ACCESS  not-accessible
      STATUS      current
      DESCRIPTION
              "Ethernet 2 IPv6 custom address table."
      ::= { ipv6Info 3 }
      
  ipv6AddressEth2Entry OBJECT-TYPE
      SYNTAX      Ipv6AddressEth2Entry
      MAX-ACCESS  not-accessible
      STATUS      current
      DESCRIPTION
              "Ethernet 2 IPv6 custom entry."
      INDEX   { ipv6AddressEth2Index }
      ::= { ipv6AddressEth2Table 1 }
      
  Ipv6AddressEth2Entry ::=
      SEQUENCE {
        ipv6AddressEth2Index              GenericTableIndex,
        ipv6AddressEth2Status              ContainerStatus,
        ipv6AddressEth2Addr              Ipv4v6Address,
        ipv6AddressEth2PrefixBits              Integer32,
		ipv6AddressEth2Auto			OnOffValue,
		ipv6AddressEth2SendAdvertise			OnOffValue
      }
	  
  ipv6AddressEth2Index OBJECT-TYPE
      SYNTAX      GenericTableIndex
      MAX-ACCESS  not-accessible
      STATUS      current
      DESCRIPTION
              "Ethernet 2 custom IPv6 address index."
      ::= { ipv6AddressEth2Entry 1 }
      
  ipv6AddressEth2Status OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ipv6AddressEth2Entry 2 }
      
  ipv6AddressEth2Addr OBJECT-TYPE
      SYNTAX      Ipv4v6Address
      MAX-ACCESS  read-write
      STATUS      current
      DESCRIPTION
              "(Ethernet 2) Either enter a network prefix that the Device 
               Server will use to derive an IPv6 address using the Device 
               Server's MAC address or enter a specific IPv6 address."
      ::= { ipv6AddressEth2Entry 3 }
      
  ipv6AddressEth2PrefixBits OBJECT-TYPE
      SYNTAX      Integer32(0..128)
      MAX-ACCESS  read-write
      STATUS      current
      DESCRIPTION
              "(Ethernet 2) The IPv6 prefix bits of either the network or
               IPv6 address."
      ::= { ipv6AddressEth2Entry 4 }
      
  ipv6AddressEth2Auto  OBJECT-TYPE
      SYNTAX   OnOffValue
      MAX-ACCESS    read-write
      STATUS        current
      DESCRIPTION
                "(Ethernet 2) When on, the Device Server will derive 
                 an IPv6 address from the entered network prefix and the 
                 Device Server's MAC address."
      ::= {ipv6AddressEth2Entry 5}
	  
  ipv6AddressEth2SendAdvertise  OBJECT-TYPE
      SYNTAX   OnOffValue
      MAX-ACCESS    read-write
      STATUS        current
      DESCRIPTION
                "(Ethernet 2) When on, the Device Server will include
                 the IPv6 address in router advertisements."
      ::= {ipv6AddressEth2Entry 6}
  
--	Eth 3
  ipv6AddressEth3Table OBJECT-TYPE
      SYNTAX      SEQUENCE OF Ipv6AddressEth3Entry
      MAX-ACCESS  not-accessible
      STATUS      current
      DESCRIPTION
              "Ethernet 3 IPv6 custom address table."
      ::= { ipv6Info 4 }
      
  ipv6AddressEth3Entry OBJECT-TYPE
      SYNTAX      Ipv6AddressEth3Entry
      MAX-ACCESS  not-accessible
      STATUS      current
      DESCRIPTION
              "Ethernet 3 IPv6 custom entry."
      INDEX   { ipv6AddressEth3Index }
      ::= { ipv6AddressEth3Table 1 }
      
    Ipv6AddressEth3Entry ::=
      SEQUENCE {
        ipv6AddressEth3Index            GenericTableIndex,
        ipv6AddressEth3Status           ContainerStatus,
        ipv6AddressEth3Addr             Ipv4v6Address,
        ipv6AddressEth3PrefixBits       Integer32,
		ipv6AddressEth3Auto				OnOffValue,
		ipv6AddressEth3SendAdvertise	OnOffValue
      }
	  
  ipv6AddressEth3Index OBJECT-TYPE
      SYNTAX      GenericTableIndex
      MAX-ACCESS  not-accessible
      STATUS      current
      DESCRIPTION
              "Ethernet 3 custom IPv6 address index."
      ::= { ipv6AddressEth3Entry 1 }
      
  ipv6AddressEth3Status OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ipv6AddressEth3Entry 2 }
      
  ipv6AddressEth2Addr OBJECT-TYPE
      SYNTAX      Ipv4v6Address
      MAX-ACCESS  read-write
      STATUS      current
      DESCRIPTION
              "(Ethernet 2) Either enter a network prefix that the Device 
               Server will use to derive an IPv6 address using the Device 
               Server's MAC address or enter a specific IPv6 address."
      ::= { ipv6AddressEth3Entry 3 }
      
  ipv6AddressEth3PrefixBits OBJECT-TYPE
      SYNTAX      Integer32(0..128)
      MAX-ACCESS  read-write
      STATUS      current
      DESCRIPTION
              "(Ethernet 3) The IPv6 prefix bits of either the network or
               IPv6 address."
      ::= { ipv6AddressEth3Entry 4 }
      
  ipv6AddressEth3Auto  OBJECT-TYPE
      SYNTAX   OnOffValue
      MAX-ACCESS    read-write
      STATUS        current
      DESCRIPTION
                "(Ethernet 3) When on, the Device Server will derive 
                 an IPv6 address from the entered network prefix and the 
                 Device Server's MAC address."
      ::= {ipv6AddressEth3Entry 5}
	  
  ipv6AddressEth3SendAdvertise  OBJECT-TYPE
      SYNTAX   OnOffValue
      MAX-ACCESS    read-write
      STATUS        current
      DESCRIPTION
                "(Ethernet 3) When on, the Device Server will include
                 the IPv6 address in router advertisements."
      ::= {ipv6AddressEth3Entry 6}
  

  -- IPv6 Tunnel Table
  
  ipv6TunnelTable OBJECT-TYPE
      SYNTAX      SEQUENCE OF Ipv6TunnelEntry
      MAX-ACCESS  not-accessible
      STATUS      current
      DESCRIPTION
              "IPv6 tunnel table."
      ::= { ipv6Info 4 }
      
  ipv6TunnelEntry OBJECT-TYPE
      SYNTAX      Ipv6TunnelEntry
      MAX-ACCESS  not-accessible
      STATUS      current
      DESCRIPTION
              "IPv6 tunnel entry."
      INDEX   { ipv6TunnelIndex }
      ::= { ipv6TunnelTable 1 }
      
  Ipv6TunnelEntry ::=
      SEQUENCE {
        ipv6TunnelIndex              GenericTableIndex,
        ipv6TunnelStatus              ContainerStatus,
        ipv6TunnelName              DisplayString,
        ipv6TunnelMode              INTEGER,
        ipv6TunnelRemoteHost              DisplayString,
        ipv6TunnelGateway              DisplayString
      }
      
  ipv6TunnelIndex OBJECT-TYPE
      SYNTAX      GenericTableIndex
      MAX-ACCESS  not-accessible
      STATUS      current
      DESCRIPTION
              "The IPv6 tunnel index entry."
      ::= { ipv6TunnelEntry 1 }
      
  ipv6TunnelStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { ipv6TunnelEntry 2 }
      
  ipv6TunnelName OBJECT-TYPE
      SYNTAX      DisplayString
      MAX-ACCESS  read-write
      STATUS      current
      DESCRIPTION
              "The name of the IPv6 tunnel. Maximum 16 alphanumeric characters."
      ::= { ipv6TunnelEntry 3 }
      
  ipv6TunnelMode OBJECT-TYPE
      SYNTAX      INTEGER {
        manual(0),
        ip6to4(1),
        teredo(2)
      }
      MAX-ACCESS  read-write
      STATUS      current
      DESCRIPTION
              "The method or protocol that is used to create the IPv6 tunnel.
               o Manual-When specified, the Device Server will manually create the IPv6 
                 tunnel to the specified Remote Host through the specified Interface.
               o ip6to4-When specified, the IOLAN will broadcast to the multicast 
                 address 192.88.99.1 through the specified Interface. When the 
                 closest ip6to4 router responds, it will create the IPv6 tunnel, 
                 encapsulating and decapsulating IPv6 traffic sent to and from 
                 the Device Server.
               o Teredo-When specified, the Teredo protocol encapsulates the IPv6 
                 packet as an IPv4 UDP message, allowing it to pass through most 
                 network address translator (NAT) boxes and create an IPv6 tunnel 
                 to the specified Remote Host (a Teredo server) through the 
                 specified Interface. 
               Default is Manual."
      ::= { ipv6TunnelEntry 4 }
      
  ipv6TunnelRemoteHost OBJECT-TYPE
      SYNTAX      DisplayString
      MAX-ACCESS  read-write
      STATUS      current
      DESCRIPTION
              "The IPv4 host that can access the IPv6 network when the Mode 
               is Manual. The Teredo server when the Mode is Teredo. "
      ::= { ipv6TunnelEntry 5 }
      
  ipv6TunnelGateway OBJECT-TYPE
      SYNTAX      DisplayString(SIZE(0..20))
      MAX-ACCESS  read-write
      STATUS      current
      DESCRIPTION
              "The interface that the Device Server is going to use to access 
               the Remote Host. The list is comprised of the Ethernet interface(s),  
               the line names configured for the PPP or SLIP, or the default line
               names configured for PPP or SLIP using serial_port_x (where x=line 
               number). Default is ethernet_1. "
      ::= { ipv6TunnelEntry 6 }

-- L2TP Info

  l2tpStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {l2tpInfo 1}

  l2tpIpsec  OBJECT-TYPE
      SYNTAX   OnOffValue
      MAX-ACCESS    read-write
      STATUS        current
      DESCRIPTION
                "When on, listens for L2TP/IPsec VPN tunnel connections. 
                 Note: to allow non-VPN tunnel connections to the Device Server, 
                 you must create entries in the VPN Exceptions list."
      ::= {l2tpInfo 2}

  l2tpAuthMethod OBJECT-TYPE
      SYNTAX      INTEGER {
        sharedSecret(0),
        x509Certificate(3)
      }
      MAX-ACCESS  read-write
      STATUS      current
      DESCRIPTION
              "The type of authentication Method that the L2TP IPsec tunnel will use."
      ::= {l2tpInfo 3 }
      
  l2tpSecret OBJECT-TYPE
      SYNTAX      DisplayString(SIZE(0..16))
      MAX-ACCESS  read-write
      STATUS      current
      DESCRIPTION
              "The L2TP/IPsec and IPsec tunnel secret. This applies to all Shared
               Secret VPN tunnels."
      ::= { l2tpInfo 4 }

  l2tpIpsecLocalIpAddr OBJECT-TYPE
      SYNTAX      IpAddress
      MAX-ACCESS  read-write
      STATUS      current
      DESCRIPTION
              "The IPv4 address that the Device Server will listen on for L2TP/IPsec
               connections. If the default value (0.0.0.0) is kept, the Device Server 
               will use the Default Gateway value (if no Default Gateway is specified, 
               L2TP/IPsec VPN connections will error out)."
      ::= { l2tpInfo 5}

  l2tpCountry    OBJECT-TYPE
      SYNTAX      DisplayString(SIZE(0..2))
      MAX-ACCESS    read-write
      STATUS        current
      DESCRIPTION
                "A two character country code; for example, US."
      ::= {l2tpInfo 6}

  l2tpStateProv    OBJECT-TYPE
      SYNTAX      DisplayString(SIZE(0..128))
      MAX-ACCESS    read-write
      STATUS        current
      DESCRIPTION
                "Up to a 128 character entry for the state/province;
                 for example, IL."
      ::= {l2tpInfo 7}

  l2tpLocality    OBJECT-TYPE
      SYNTAX      DisplayString(SIZE(0..128))
      MAX-ACCESS    read-write
      STATUS        current
      DESCRIPTION
                "Up to a 128 character entry for the location; 
                 for example, a city."
      ::= {l2tpInfo 8}

  l2tpOrganisation    OBJECT-TYPE
      SYNTAX      DisplayString(SIZE(0..64))
      MAX-ACCESS    read-write
      STATUS        current
      DESCRIPTION
                "Up to a 64 character entry for the organization; 
                 for example, Accounting."
      ::= {l2tpInfo 9}

  l2tpOrganisationUnit    OBJECT-TYPE
      SYNTAX      DisplayString(SIZE(0..64))
      MAX-ACCESS    read-write
      STATUS        current
      DESCRIPTION
                "Up to a 64 character entry for the unit in the 
                 organization; for example, Payroll."
      ::= {l2tpInfo 10}

  l2tpCommonName    OBJECT-TYPE
      SYNTAX      DisplayString(SIZE(0..64))
      MAX-ACCESS    read-write
      STATUS        current
      DESCRIPTION
                "Up to a 64 character entry for common name; for example,
                 the host name or fully qualified domain name."
      ::= {l2tpInfo 11}

  l2tpEmail    OBJECT-TYPE
      SYNTAX      DisplayString(SIZE(0..128))
      MAX-ACCESS    read-write
      STATUS        current
      DESCRIPTION
                "Up to a 64 character entry for an email address; 
                 for example, acct@anycompany.com."
      ::= {l2tpInfo 12}
	  
  l2tpPPPLocalIpAddr OBJECT-TYPE
      SYNTAX      IpAddress
      MAX-ACCESS  read-write
      STATUS      current
      DESCRIPTION
              "Specify the unique IPv4 address that hosts accessing the 
               Device Server through the L2TP tunnel will use."
      ::= { l2tpInfo 13}

  l2tpPPPRemoteStartIpAddr OBJECT-TYPE
      SYNTAX      IpAddress
      MAX-ACCESS  read-write
      STATUS      current
      DESCRIPTION
              "Specify the first IPv4 address that can be assigned to 
               incoming hosts through the L2TP tunnel."
      ::= { l2tpInfo 14}

  l2tpPPPRemoteEndIpAddr OBJECT-TYPE
      SYNTAX      IpAddress
      MAX-ACCESS  read-write
      STATUS      current
      DESCRIPTION
              "Specify the end range of the IPv4 addresses that can be 
               assigned to incoming hosts through the L2TP tunnel."
      ::= { l2tpInfo 15}
  
  l2tpPap  OBJECT-TYPE
      SYNTAX   OnOffValue
      MAX-ACCESS    read-write
      STATUS        current
      DESCRIPTION
                "Use the PAP authentication method that will be used for 
                 the L2TP tunnel."
      ::= {l2tpInfo 16}

  l2tpChap  OBJECT-TYPE
      SYNTAX   OnOffValue
      MAX-ACCESS    read-write
      STATUS        current
      DESCRIPTION
                "Use the CHAP authentication method that will be used for 
                 the L2TP tunnel. This is the default."
      ::= {l2tpInfo 17}

-- VPN exception Info

   vpnexceptionTable OBJECT-TYPE
      SYNTAX      SEQUENCE OF VpnexceptionEntry
      MAX-ACCESS  not-accessible
      STATUS      current
      DESCRIPTION
              "vpnexceptionTable"
      ::= { vpnexceptionInfo 1}

   vpnexceptionEntry OBJECT-TYPE
      SYNTAX      VpnexceptionEntry
      MAX-ACCESS  not-accessible
      STATUS      current
      DESCRIPTION
               "vpnexceptionEntry"
      INDEX   { vpnexceptionIndex }
      ::= { vpnexceptionTable 1 }

   VpnexceptionEntry ::=
      SEQUENCE {
        vpnexceptionIndex              GenericTableIndex,
        vpnexceptionStatus            ContainerStatus,
        vpnexceptionIpAddress            Ipv4v6Address,
        vpnexceptionPrefixBits            Integer32
          }

   vpnexceptionIndex OBJECT-TYPE
      SYNTAX      GenericTableIndex
      MAX-ACCESS not-accessible
      STATUS      current
      DESCRIPTION
              "vpnexceptionIndex"
      ::= { vpnexceptionEntry 1}

   vpnexceptionStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= { vpnexceptionEntry 2}

   vpnexceptionIpAddress OBJECT-TYPE
      SYNTAX      Ipv4v6Address
      MAX-ACCESS  read-write
      STATUS      current
      DESCRIPTION
              "The IPv4 or IPv6 address of the host or network that will communicate with 
               the Device Server outside of the VPN tunnel."
      ::= { vpnexceptionEntry 3}

   vpnexceptionPrefixBits OBJECT-TYPE
      SYNTAX      Integer32(0..128)
      MAX-ACCESS  read-write
      STATUS      current
      DESCRIPTION
              "The IPv4 subnet bits or IPv6 prefix bits for the network. 0-128."
      ::= { vpnexceptionEntry 4}
  

  
-- HTTP Tunneling info BEGINS  

httpTunCfg              OBJECT IDENTIFIER ::= { httpTunInfo 1 }

httpTunTunnelCfg        OBJECT IDENTIFIER ::= { httpTunCfg 1 }
httpTunConnectionCfg    OBJECT IDENTIFIER ::= { httpTunCfg 2 }

httpTunProxyCfg         OBJECT IDENTIFIER ::= { httpTunTunnelCfg 2 }

httpTunProxyBasic       OBJECT IDENTIFIER ::= { httpTunProxyCfg 1 }
httpTunProxyAdv         OBJECT IDENTIFIER ::= { httpTunProxyCfg 2 }

httpTunStats            OBJECT IDENTIFIER ::= { httpTunInfo 2 }

httpTunTunnelStats      OBJECT IDENTIFIER ::= { httpTunStats 1 }
httpTunConnectionStats  OBJECT IDENTIFIER ::= { httpTunStats 2 }

-- HTTP Tunneling: Proxy

httpTunProxyBasicStatus OBJECT-TYPE
  SYNTAX      ContainerStatus
  MAX-ACCESS  read-write
  STATUS      current
  DESCRIPTION
          "When you perform a GET on this variable, one of
           the following values will be returned:
           1-Indicates that the container folder is active with no changes.
           2-Indicates that the container folder is active with change(s).
           Once you have completed setting the variables in a folder, you
           will want to submit your changes to the Device Server. To do
           this, set the Status variable to 4. If you want to discard the
           changes, set the Status variable to 6.
           4-Indicates that the changes in the container folder are to be
             submitted to the Device Server.
           6-Indicates that the changes in the container folder are to be
             discarded."
  ::= { httpTunProxyBasic 1 }


httpTunProxyHost OBJECT-TYPE
  SYNTAX      DisplayString(SIZE(0..50))
  MAX-ACCESS  read-write
  STATUS      current
  DESCRIPTION
          "The hostname/IP address of the HTTP proxy."
  ::= { httpTunProxyBasic 2 }

httpTunProxyPort OBJECT-TYPE
  SYNTAX      Integer32(1..65535)
  MAX-ACCESS  read-write
  STATUS      current
  DESCRIPTION
          "The port number for connecting to the HTTP proxy."
  ::= { httpTunProxyBasic 3 }

httpTunProxyUser OBJECT-TYPE
  SYNTAX      DisplayString(SIZE(0..80))
  MAX-ACCESS  read-write
  STATUS      current
  DESCRIPTION
          "The username for the HTTP proxy, if authentication is required."
  ::= { httpTunProxyBasic 4 }

httpTunProxyPassword OBJECT-TYPE
  SYNTAX      DisplayString(SIZE(0..80))
  MAX-ACCESS  read-write
  STATUS      current
  DESCRIPTION
          "The password for the HTTP proxy, if authentication is required."
  ::= { httpTunProxyBasic 5 }

httpTunProxyDomain OBJECT-TYPE
  SYNTAX      DisplayString(SIZE(0..80))
  MAX-ACCESS  read-write
  STATUS      current
  DESCRIPTION
          "The NTLM domain for the HTTP proxy.  This is only required
           if the proxy is using NTLM authentication."
  ::= { httpTunProxyBasic 6 }


httpTunProxyAdvStatus OBJECT-TYPE
  SYNTAX      ContainerStatus
  MAX-ACCESS  read-write
  STATUS      current
  DESCRIPTION
          "When you perform a GET on this variable, one of
           the following values will be returned:
           1-Indicates that the container folder is active with no changes.
           2-Indicates that the container folder is active with change(s).
           Once you have completed setting the variables in a folder, you
           will want to submit your changes to the Device Server. To do
           this, set the Status variable to 4. If you want to discard the
           changes, set the Status variable to 6.
           4-Indicates that the changes in the container folder are to be
             submitted to the Device Server.
           6-Indicates that the changes in the container folder are to be
             discarded."
  ::= { httpTunProxyAdv 1 }





httpTunProxyKeepaliveInterval OBJECT-TYPE
  SYNTAX      Integer32(1..255)
  MAX-ACCESS  read-write
  STATUS      current
  DESCRIPTION
          "Keepalive interval for HTTP tunneling, in seconds"
  ::= { httpTunProxyAdv 2 }

httpTunProxyMaxConnectionAge OBJECT-TYPE

  SYNTAX      Integer32(1..65535)
  MAX-ACCESS  read-write
  STATUS      current
  DESCRIPTION
          "Maximum connection age for HTTP tunneling, in minutes."
  ::= { httpTunProxyAdv 3 }

-- HTTP Tunneling: Tunnel config


httpTunTunnelCfgTable OBJECT-TYPE
  SYNTAX      SEQUENCE OF HttpTunTunnelCfgEntry
  MAX-ACCESS  not-accessible
  STATUS      current
  DESCRIPTION
          "The httpTunTunnelCfg table."
  ::= { httpTunTunnelCfg 1 }

httpTunTunnelCfgEntry OBJECT-TYPE
  SYNTAX      HttpTunTunnelCfgEntry
  MAX-ACCESS  not-accessible
  STATUS      current
  DESCRIPTION
          "An entry in the httpTunTunnelCfgEntry, each relating to a tunnel."
  INDEX   { httpTunTunnelCfgIndex }
  ::= { httpTunTunnelCfgTable 1 }

HttpTunTunnelCfgEntry ::=
  SEQUENCE {
    httpTunTunnelCfgIndex        GenericTableIndex,
    httpTunTunnelCfgStatus        ContainerStatus,
    httpTunTunnelCfgValid        OnOffValue,
    httpTunTunnelCfgName        DisplayString,
    httpTunTunnelCfgMode        INTEGER,
    httpTunTunnelCfgConnectHost        DisplayString,
    httpTunTunnelCfgConnectUseProxy        OnOffValue,
    httpTunTunnelCfgListenRestrictIp        Ipv4v6Address,
    httpTunTunnelCfgHttps        OnOffValue,
    httpTunTunnelCfgRestrictAccess        OnOffValue,
    httpTunTunnelCfgSecret        DisplayString
}

httpTunTunnelCfgIndex OBJECT-TYPE
  SYNTAX      GenericTableIndex
  MAX-ACCESS  not-accessible
  STATUS      current
  DESCRIPTION
          "The table entry number for this tunnel."
  ::= { httpTunTunnelCfgEntry 1 }

httpTunTunnelCfgStatus OBJECT-TYPE
  SYNTAX      ContainerStatus
  MAX-ACCESS  read-write
  STATUS      current
  DESCRIPTION
          "When you perform a GET on this variable, one of
           the following values will be returned:
           1-Indicates that the container folder is active with no changes.
           2-Indicates that the container folder is active with change(s).
           Once you have completed setting the variables in a folder, you
           will want to submit your changes to the Device Server. To do
           this, set the Status variable to 4. If you want to discard the
           changes, set the Status variable to 6.
           4-Indicates that the changes in the container folder are to be
             submitted to the Device Server.
           6-Indicates that the changes in the container folder are to be
             discarded."
    ::= { httpTunTunnelCfgEntry 2}
    
httpTunTunnelCfgValid OBJECT-TYPE
  SYNTAX      OnOffValue
  MAX-ACCESS  read-write
  STATUS      current
  DESCRIPTION
          "Specifies whether this tunnel is valid or not."
  ::= { httpTunTunnelCfgEntry 3 }

httpTunTunnelCfgName OBJECT-TYPE
  SYNTAX      DisplayString(SIZE(0..14))
  MAX-ACCESS  read-write
  STATUS      current
  DESCRIPTION
          "The name of this tunnel.  Tunnel names should be unique."
  ::= { httpTunTunnelCfgEntry 4 }

httpTunTunnelCfgMode OBJECT-TYPE
      SYNTAX      INTEGER {
        listen(1),
        connect(2)
      }
  MAX-ACCESS  read-write
  STATUS      current
  DESCRIPTION
          "Specifies whether this tunnel endpoint should listen or connect.  A 
           functional HTTP tunnel consists of two endpoints: a listener and a connecter."
  ::= { httpTunTunnelCfgEntry 5 }

httpTunTunnelCfgConnectHost OBJECT-TYPE
  SYNTAX      DisplayString(SIZE(0..50))
  MAX-ACCESS  read-write
  STATUS      current
  DESCRIPTION
          "For tunnels in connect mode, specifies the remote host to 
           connect to."
  ::= { httpTunTunnelCfgEntry 6 }


httpTunTunnelCfgConnectUseProxy OBJECT-TYPE
  SYNTAX      OnOffValue
  MAX-ACCESS  read-write
  STATUS      current
  DESCRIPTION
          "For tunnels in connect mode, specifies whether to use 
           an HTTP proxy."
  ::= { httpTunTunnelCfgEntry 7 }


httpTunTunnelCfgListenRestrictIp OBJECT-TYPE
  SYNTAX      Ipv4v6Address
  MAX-ACCESS  read-write
  STATUS      current
  DESCRIPTION
          "For tunnels in listen mode, specifies whether to  
           restrict the other tunnel endpoint to a fixed IP address.
           Use 0.0.0.0 for no restriction"
  ::= { httpTunTunnelCfgEntry 8 }

httpTunTunnelCfgHttps OBJECT-TYPE
  SYNTAX      OnOffValue
  MAX-ACCESS  read-write
  STATUS      current
  DESCRIPTION
          "Specifies whether this tunnel should use HTTPS for communication."
  ::= { httpTunTunnelCfgEntry 9 }

httpTunTunnelCfgRestrictAccess OBJECT-TYPE
  SYNTAX      OnOffValue
  MAX-ACCESS  read-write
  STATUS      current
  DESCRIPTION
          "Specifies whether this tunnel should restrict access to local
           connections."
  ::= { httpTunTunnelCfgEntry 10 }

httpTunTunnelCfgSecret OBJECT-TYPE
  SYNTAX      DisplayString(SIZE(0..50))
  MAX-ACCESS  read-write
  STATUS      current
  DESCRIPTION
          "Specifies the shared secret for this tunnel.  If the shared secret
           blank, the tunnel will be unauthenticated."
  ::= { httpTunTunnelCfgEntry 11 }




-- HTTP Tunneling: Tunnel stats


httpTunTunnelStatsTable OBJECT-TYPE
  SYNTAX      SEQUENCE OF HttpTunTunnelStatsEntry
  MAX-ACCESS  not-accessible
  STATUS      current
  DESCRIPTION
          "The httpTunTunnelStats table."
  ::= { httpTunTunnelStats 1 }

httpTunTunnelStatsEntry OBJECT-TYPE
  SYNTAX      HttpTunTunnelStatsEntry
  MAX-ACCESS  not-accessible
  STATUS      current
  DESCRIPTION
          "An entry in the httpTunTunnelStatsEntry, each relating to a tunnel."
  INDEX   { httpTunTunnelStatsIndex }
  ::= { httpTunTunnelStatsTable 1 }

HttpTunTunnelStatsEntry ::=
  SEQUENCE {
    httpTunTunnelStatsIndex        GenericTableIndex,
    httpTunTunnelStatsName        DisplayString,
    httpTunTunnelStatsMode        INTEGER,
    httpTunTunnelStatsConnectHost        DisplayString,
    httpTunTunnelStatsConnected          YesNoValue,
    httpTunTunnelStatsHttps              YesNoValue,
    httpTunTunnelStatsAuthFailed         YesNoValue
}

httpTunTunnelStatsIndex OBJECT-TYPE
  SYNTAX      GenericTableIndex
  MAX-ACCESS  not-accessible
  STATUS      current
  DESCRIPTION
          "The table entry number for this tunnel."
  ::= { httpTunTunnelStatsEntry 1 }
    
httpTunTunnelStatsName OBJECT-TYPE
  SYNTAX      DisplayString(SIZE(0..14))
  MAX-ACCESS  read-only
  STATUS      current
  DESCRIPTION
          "The name of this tunnel."
  ::= { httpTunTunnelStatsEntry 2 }

httpTunTunnelStatsMode OBJECT-TYPE
      SYNTAX      INTEGER {
        listen(1),
        connect(2)
      }
  MAX-ACCESS  read-only
  STATUS      current
  DESCRIPTION
          "Specifies whether this tunnel endpoint is listening or connecting."
  ::= { httpTunTunnelStatsEntry 3 }

httpTunTunnelStatsConnectHost OBJECT-TYPE
  SYNTAX      DisplayString(SIZE(0..50))
  MAX-ACCESS  read-only
  STATUS      current
  DESCRIPTION
          "For tunnels in connect mode, specifies the remote host to 
           connect to."
  ::= { httpTunTunnelStatsEntry 4 }


httpTunTunnelStatsConnected OBJECT-TYPE
  SYNTAX      YesNoValue
  MAX-ACCESS  read-only
  STATUS      current
  DESCRIPTION
          "Specifies whether this tunnel is connected."
  ::= { httpTunTunnelStatsEntry 5 }


httpTunTunnelStatsHttps OBJECT-TYPE
  SYNTAX      YesNoValue
  MAX-ACCESS  read-only
  STATUS      current
  DESCRIPTION
          "Specifies whether this tunnel is using HTTPS for communication."
  ::= { httpTunTunnelStatsEntry 6 }

httpTunTunnelStatsAuthFailed OBJECT-TYPE
  SYNTAX      YesNoValue
  MAX-ACCESS  read-only
  STATUS      current
  DESCRIPTION
          "Specifies whether authentication failed for this tunnel."
  ::= { httpTunTunnelStatsEntry 7 }


-- HTTP Tunneling: Connections config

httpTunConnectionCfgTable OBJECT-TYPE
  SYNTAX      SEQUENCE OF HttpTunConnectionCfgEntry
  MAX-ACCESS  not-accessible
  STATUS      current
  DESCRIPTION
          "The httpTunConnectionCfg table."
  ::= { httpTunConnectionCfg 1 }

httpTunConnectionCfgEntry OBJECT-TYPE
  SYNTAX      HttpTunConnectionCfgEntry
  MAX-ACCESS  not-accessible
  STATUS      current
  DESCRIPTION
          "An entry in the httpTunConnectionCfgEntry, each relating to a Connection."
  INDEX   { httpTunConnectionCfgIndex }
  ::= { httpTunConnectionCfgTable 1 }

HttpTunConnectionCfgEntry ::=
  SEQUENCE {
    httpTunConnectionCfgIndex        GenericTableIndex,
    httpTunConnectionCfgStatus        ContainerStatus,    
    httpTunConnectionCfgValid        OnOffValue,
    httpTunConnectionCfgTunnelName        DisplayString,
    httpTunConnectionCfgProtocol        INTEGER,    
    httpTunConnectionCfgDestinationHost    DisplayString,    
    httpTunConnectionCfgDestinationPort        Integer32,
    httpTunConnectionCfgLocalPort        Integer32,
    httpTunConnectionCfgLocalIpAlias        IpAddress,
    httpTunConnectionCfgRestrictAccess        OnOffValue
}

httpTunConnectionCfgIndex OBJECT-TYPE
  SYNTAX      GenericTableIndex
  MAX-ACCESS  not-accessible
  STATUS      current
  DESCRIPTION
          "The table entry number for this Connection."
  ::= { httpTunConnectionCfgEntry 1 }

httpTunConnectionCfgStatus OBJECT-TYPE
  SYNTAX      ContainerStatus
  MAX-ACCESS  read-write
  STATUS      current
  DESCRIPTION
          "When you perform a GET on this variable, one of
           the following values will be returned:
           1-Indicates that the container folder is active with no changes.
           2-Indicates that the container folder is active with change(s).
           Once you have completed setting the variables in a folder, you
           will want to submit your changes to the Device Server. To do
           this, set the Status variable to 4. If you want to discard the
           changes, set the Status variable to 6.
           4-Indicates that the changes in the container folder are to be
             submitted to the Device Server.
           6-Indicates that the changes in the container folder are to be
             discarded."
  ::= { httpTunConnectionCfgEntry 2}

httpTunConnectionCfgValid OBJECT-TYPE
  SYNTAX      OnOffValue
  MAX-ACCESS  read-write
  STATUS      current
  DESCRIPTION
          "Specifies whether this Connection is valid or not."
  ::= { httpTunConnectionCfgEntry 3 }

httpTunConnectionCfgTunnelName OBJECT-TYPE
  SYNTAX      DisplayString(SIZE(0..14))
  MAX-ACCESS  read-write
  STATUS      current
  DESCRIPTION
          "The name of the tunnel associated with this connection."
  ::= { httpTunConnectionCfgEntry 4 }

httpTunConnectionCfgProtocol OBJECT-TYPE
      SYNTAX      INTEGER {
        tcp(1),
        udp(2)
      }
  MAX-ACCESS  read-write
  STATUS      current
  DESCRIPTION
          "The protocol used by this connection."
  ::= { httpTunConnectionCfgEntry 5 }

httpTunConnectionCfgDestinationHost OBJECT-TYPE
  SYNTAX      DisplayString(SIZE(0..50))
  MAX-ACCESS  read-write
  STATUS      current
  DESCRIPTION
          "The destination host for this connection.  Application traffic tunneled in this 
           connection will be forwarded to this host."
  ::= { httpTunConnectionCfgEntry 6 }

httpTunConnectionCfgDestinationPort OBJECT-TYPE
  SYNTAX      Integer32(0..65535)
  MAX-ACCESS  read-write
  STATUS      current
  DESCRIPTION
          "The destination port for this connection.  Application traffic tunneled in this 
           connection will be forwarded to this TCP/UDP port."
  ::= { httpTunConnectionCfgEntry 7 }


httpTunConnectionCfgLocalPort OBJECT-TYPE
  SYNTAX      Integer32(0..65535)
  MAX-ACCESS  read-write
  STATUS      current
  DESCRIPTION
          "The local listening port for this connection.  Application that wish to use
          this tunnel/connection should connect to this TCP/UDP port on the device server."
  ::= { httpTunConnectionCfgEntry 8 }

httpTunConnectionCfgLocalIpAlias OBJECT-TYPE
  SYNTAX      IpAddress
  MAX-ACCESS  read-write
  STATUS      current
  DESCRIPTION
          "(Optional) Specifies the local IP alias for this connection.  If specified,
           application who wish to use this tunnel/connection can connect to the local IP alias
           and TCP/UDP port.  This is useful when you want to create several connections 
           with the same local listening TCP/UDP port.
           
           Use 0.0.0.0 to specify no IP alias."
  ::= { httpTunConnectionCfgEntry 9 }

httpTunConnectionCfgRestrictAccess OBJECT-TYPE
  SYNTAX      OnOffValue
  MAX-ACCESS  read-write
  STATUS      current
  DESCRIPTION
          "Specifies whether to restrict access to local application traffic only."
  ::= { httpTunConnectionCfgEntry 10 }



-- HTTP Tunneling: Connections stats

httpTunConnectionStatsTable OBJECT-TYPE
  SYNTAX      SEQUENCE OF HttpTunConnectionStatsEntry
  MAX-ACCESS  not-accessible
  STATUS      current
  DESCRIPTION
          "The httpTunConnectionStats table."
  ::= { httpTunConnectionStats 1 }

httpTunConnectionStatsEntry OBJECT-TYPE
  SYNTAX      HttpTunConnectionStatsEntry
  MAX-ACCESS  not-accessible
  STATUS      current
  DESCRIPTION
          "An entry in the httpTunConnectionStatsEntry, each relating to a Connection."
  INDEX   { httpTunConnectionStatsIndex }
  ::= { httpTunConnectionStatsTable 1 }

HttpTunConnectionStatsEntry ::=
  SEQUENCE {
    httpTunConnectionStatsIndex        GenericTableIndex,
    httpTunConnectionStatsTunnelName        DisplayString,
    httpTunConnectionStatsType        INTEGER,
    httpTunConnectionStatsProtocol        INTEGER,
    httpTunConnectionStatsDestinationIp        Ipv4v6Address,
    httpTunConnectionStatsDestinationPort        Integer32,
    httpTunConnectionStatsSourceIp        Ipv4v6Address,
    httpTunConnectionStatsLocalPort        Integer32
  }

httpTunConnectionStatsIndex OBJECT-TYPE
  SYNTAX      GenericTableIndex
  MAX-ACCESS  not-accessible
  STATUS      current
  DESCRIPTION
          "The table entry number for this connection."
  ::= { httpTunConnectionStatsEntry 1 }

httpTunConnectionStatsTunnelName OBJECT-TYPE
  SYNTAX      DisplayString(SIZE(0..14))
  MAX-ACCESS  read-only
  STATUS      current
  DESCRIPTION
          "The name of the tunnel associated with this connection."
  ::= { httpTunConnectionStatsEntry 2 }

httpTunConnectionStatsType OBJECT-TYPE
      SYNTAX      INTEGER {
        direct(2),
        reverse(3)
      }
  MAX-ACCESS  read-only
  STATUS      current
  DESCRIPTION
          "The type of connection:
            direct - Originating from this end of tunnel
            reverse - Originating from other end of tunnel"
  ::= { httpTunConnectionStatsEntry 3 }

httpTunConnectionStatsProtocol OBJECT-TYPE
      SYNTAX      INTEGER {
        tcp(1),
        udp(2)
      }
  MAX-ACCESS  read-only
  STATUS      current
  DESCRIPTION
          "The protocol used by this connection."
  ::= { httpTunConnectionStatsEntry 4 }

httpTunConnectionStatsDestinationIp OBJECT-TYPE
  SYNTAX      Ipv4v6Address
  MAX-ACCESS  read-only
  STATUS      current
  DESCRIPTION
          "The destination IP for this connection."
  ::= { httpTunConnectionStatsEntry 5 }

httpTunConnectionStatsDestinationPort OBJECT-TYPE
  SYNTAX      Integer32(0..65535)
  MAX-ACCESS  read-only
  STATUS      current
  DESCRIPTION
          "The destination port for this connection."
  ::= { httpTunConnectionStatsEntry 6 }


httpTunConnectionStatsSourceIp OBJECT-TYPE
  SYNTAX      Ipv4v6Address
  MAX-ACCESS  read-only
  STATUS      current
  DESCRIPTION
          "The source (originating) IP for this connection."
  ::= { httpTunConnectionStatsEntry 7 }

httpTunConnectionStatsLocalPort OBJECT-TYPE
  SYNTAX      Integer32(0..65535)
  MAX-ACCESS  read-only
  STATUS      current
  DESCRIPTION
          "The local listening port for this connection."
  ::= { httpTunConnectionStatsEntry 8 }


-- HTTP Tunneling info ENDS



-- WLAN info BEGINS

wlanCfg                OBJECT IDENTIFIER ::= { wlanInfo 1 }
wlanStats              OBJECT IDENTIFIER ::= { wlanInfo 2 }

wlanGlobalCfg          OBJECT IDENTIFIER ::= { wlanCfg 1 }
wlanProfilesCfg        OBJECT IDENTIFIER ::= { wlanCfg 2 }
wlanSoftapCfg          OBJECT IDENTIFIER ::= { wlanCfg 3 }


--  wlanGlobalCfg group start
wlanGlobalStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
         Once you have completed setting the variables in a folder, you
         will want to submit your changes to the Device Server. To do
         this, set the Status variable to 4. If you want to discard the
         changes, set the Status variable to 6.
         4-Indicates that the changes in the container folder are to be
           submitted to the Device Server.
         6-Indicates that the changes in the container folder are to be
           discarded."
    ::= {wlanGlobalCfg 1}

wlanGlobalRegion OBJECT-TYPE
    SYNTAX      DisplayString(SIZE(2..9))
    MAX-ACCESS  read-write
    STATUS      current
    DESCRIPTION
        "The name of the region where the WIFI is being used.
        
         Valid regions are:
         US-Canada, EU, or Japan"
    ::= { wlanGlobalCfg 2 }

wlanGlobalMode OBJECT-TYPE
    SYNTAX      INTEGER {
        disabled(1),
        client(2),
        softap(3)
    }
    MAX-ACCESS  read-write
    STATUS      current
    DESCRIPTION
        "The Wi-Fi operating mode.
        
         disabled:  Wi-Fi is disabled
         client:    In this mode, the IOLAN can connect to an access point.
         softap:    In this mode, the IOLAN acts as an access point allowing
                    wireless clients to connect"
    ::= { wlanGlobalCfg 3}

wlanGlobalRadioBand OBJECT-TYPE
    SYNTAX      INTEGER {
        bandBoth(1),
        band2g4(2),
        band5g(3)
    }
    MAX-ACCESS  read-write
    STATUS      current
    DESCRIPTION
        "The radio bands to use.
        
         bandBoth:     use both 2.4GHz and 5GHz bands    
         band2g4:      use 2.4GHz band only 
         band5g:       use 5GHz band only"
    ::= { wlanGlobalCfg 4}

wlanGlobalWps OBJECT-TYPE
    SYNTAX      OnOffValue
    MAX-ACCESS  read-write
    STATUS      current
    DESCRIPTION
        "Enable/disable WPS."
    ::= { wlanGlobalCfg 5 }

wlanGlobalPassiveScan OBJECT-TYPE
    SYNTAX      OnOffValue
    MAX-ACCESS  read-write
    STATUS      current
    DESCRIPTION
        "Enable/disable passive scan only."
    ::= { wlanGlobalCfg 6 }

wlanGlobalRoaming OBJECT-TYPE
    SYNTAX      OnOffValue
    MAX-ACCESS  read-write
    STATUS      current
    DESCRIPTION
        "Enable/disable roaming."
    ::= { wlanGlobalCfg 7 }

wlanGlobalRoamingDecision OBJECT-TYPE
    SYNTAX      INTEGER {
        balanced(1),
        optimizeBandwidth(2),
        optimizeDistance(3)
    }
    MAX-ACCESS  read-write
    STATUS      current
    DESCRIPTION
        "This controls how the IOLAN scans for a better access point
         within the same ESSID network."
    ::= { wlanGlobalCfg 8}

wlanGlobalRoamingOutOfRangeScanInterval OBJECT-TYPE
    SYNTAX      Integer32(0..65535)
    MAX-ACCESS  read-write
    STATUS      current
    DESCRIPTION
        "The time in seconds, between fast roaming scans."
    ::= { wlanGlobalCfg 9}

wlanGlobalRoamingInRangeScanInterval OBJECT-TYPE
    SYNTAX      Integer32(0..65535)
    MAX-ACCESS  read-write
    STATUS      current
    DESCRIPTION
        "The time in seconds, between slow roaming scans."
    ::= { wlanGlobalCfg 10}

wlanGlobalAntennaDiveristyMrc OBJECT-TYPE
    SYNTAX      OnOffValue
    MAX-ACCESS  read-write
    STATUS      current
    DESCRIPTION
        "Enable/disable antenna diversity/MRC."
    ::= { wlanGlobalCfg 11 }

--  wlanGlobalCfg group end


--  wlanSoftapCfg group start
wlanSoftapStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
         Once you have completed setting the variables in a folder, you
         will want to submit your changes to the Device Server. To do
         this, set the Status variable to 4. If you want to discard the
         changes, set the Status variable to 6.
         4-Indicates that the changes in the container folder are to be
           submitted to the Device Server.
         6-Indicates that the changes in the container folder are to be
           discarded."
    ::= {wlanSoftapCfg 1}

wlanSoftapSSID OBJECT-TYPE
    SYNTAX      DisplayString(SIZE(1..32))
    MAX-ACCESS  read-write
    STATUS      current
    DESCRIPTION
        "The IOLAN's SSID."
    ::= { wlanSoftapCfg 2}

wlanSoftapChannel OBJECT-TYPE
    SYNTAX      INTEGER {
        chan1(1),
        chan2(2),
        chan3(3),
        chan4(4),
        chan5(5),
        chan6(6),
        chan7(7),
        chan8(8),
        chan9(9),
        chan10(10),
        chan11(11),
        chan36(36),
        chan40(40),
        chan44(44),
        chan48(48)
    }
    MAX-ACCESS  read-write
    STATUS      current
    DESCRIPTION
        "The channel to use for softap mode.
         2.5GHz: 1-11
         5GHz:   36, 40, 44, 48"
    ::= { wlanSoftapCfg 3}

wlanSoftapSecurityType OBJECT-TYPE
    SYNTAX      INTEGER {
        wpa2Personal(3),
        wpaPersonal(4)
    }
    MAX-ACCESS  read-write
    STATUS      current
    DESCRIPTION
        "The security type to use."
    ::= { wlanSoftapCfg 4}

wlanSoftapEncryptionType OBJECT-TYPE
    SYNTAX      INTEGER {
        tkip(3),
        aes(4)
    }
    MAX-ACCESS  read-write
    STATUS      current
    DESCRIPTION
        "The encryption type to use."
    ::= { wlanSoftapCfg 5}

wlanSoftapSecurityKey OBJECT-TYPE
    SYNTAX      DisplayString(SIZE(8..64))
    MAX-ACCESS  read-write
    STATUS      current
    DESCRIPTION
        "The security key for WPA2-Personal/WPA-Personal.
         8-63 case sensitive characters or
         64 hexadecimal characters"
    ::= { wlanSoftapCfg 6}

wlanSoftapIpAddress OBJECT-TYPE
    SYNTAX      IpAddress
    MAX-ACCESS  read-write
    STATUS      current
    DESCRIPTION
      "The IP address of the IOLAN's WLAN interface when in softap mode."
    ::= { wlanSoftapCfg 7 }

wlanSoftapSubnetBits OBJECT-TYPE
    SYNTAX      Integer32(1..32)
    MAX-ACCESS  read-write
    STATUS      current
    DESCRIPTION
        "The number of bits in the subnet mask. For example,
         a subnet mask of 255.255.0.0 has 16 subnet/prefix bits.
         Valid values are 1-32."
    ::= { wlanSoftapCfg 8 }

wlanSoftapDhcp OBJECT-TYPE
    SYNTAX      OnOffValue
    MAX-ACCESS  read-write
    STATUS      current
    DESCRIPTION
        "Enable/disable DHCP for softap mode.
         When enabled, DHCP will assign an IP address to connecting devices."
    ::= {wlanSoftapCfg 9}	  

wlanSoftapDhcpIpPoolAddress OBJECT-TYPE
    SYNTAX      IpAddress
    MAX-ACCESS  read-write
    STATUS      current
    DESCRIPTION
      "The DHCP pool starting IP address."
    ::= { wlanSoftapCfg 10 }

wlanSoftapDhcpSubnetBits OBJECT-TYPE
    SYNTAX      Integer32(1..32)
    MAX-ACCESS  read-write
    STATUS      current
    DESCRIPTION
        "The number of bits in the subnet mask. For example,
         a subnet mask of 255.255.0.0 has 16 subnet/prefix bits.
         Valid values are 1-32."
    ::= { wlanSoftapCfg 11 }


--  wlanSoftapCfg group end


--  wlanProfilesCfg group start

wlanProfileTable OBJECT-TYPE
    SYNTAX      SEQUENCE OF WlanProfileEntry
    MAX-ACCESS  not-accessible
    STATUS      current
    DESCRIPTION
        "The WLAN profile table."
    ::= { wlanProfilesCfg 1 }

wlanProfileEntry OBJECT-TYPE
    SYNTAX      WlanProfileEntry
    MAX-ACCESS  not-accessible
    STATUS      current
    DESCRIPTION
        "An entry in the wlanProfileEntry, each relating to a WLAN profile."
    INDEX   { wlanProfileIndex }
    ::= { wlanProfileTable 1 }

WlanProfileEntry ::=
      SEQUENCE {
         wlanProfileIndex                       GenericTableIndex,
         wlanProfileStatus                      ContainerStatus,

         wlanProfileEnable                      YesNoValue,
         wlanProfileConnectPriority             Integer32,
         wlanProfileName                        DisplayString,
         wlanProfileSsid                        DisplayString,
         wlanProfileScanBand                    INTEGER,
         wlanProfileScanDfs                     OnOffValue,
         wlanProfileHiddenSsid                  YesNoValue,
         wlanProfileSecurityType                INTEGER,
         wlanProfileEncryptionType              INTEGER,
         
         wlanProfileOpenSharedWepKey1           DisplayString,
         wlanProfileOpenSharedWepKey2           DisplayString,
         wlanProfileOpenSharedWepKey3           DisplayString,
         wlanProfileOpenSharedWepKey4           DisplayString,
         wlanProfileOpenSharedWepTxKeyIndex     Integer32,
         
         wlanProfilePersonalSecurityKey         DisplayString,
         
         wlanProfileEnterpriseUsername          DisplayString,
         wlanProfileEnterprisePassword          DisplayString,
         wlanProfileEnterpriseValidateCert      OnOffValue,
         wlanProfileEnterpriseAuthMethod        INTEGER,
         wlanProfileEnterpriseAuthProtocol      INTEGER,
         wlanProfileEnterpriseRoamingIdentity   DisplayString,
         
         wlanProfile8021xUsername               DisplayString,
         wlanProfile8021xPassword               DisplayString,
         wlanProfile8021xValidateCert           OnOffValue,
         wlanProfile8021xAuthMethod             INTEGER,
         wlanProfile8021xAuthProtocol           INTEGER,
         wlanProfile8021xRoamingIdentity        DisplayString
    }

wlanProfileIndex OBJECT-TYPE
      SYNTAX      GenericTableIndex
      MAX-ACCESS  not-accessible
      STATUS      current
      DESCRIPTION
              "The table entry number for this user."
      ::= { wlanProfileEntry 1 }

wlanProfileStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
         Once you have completed setting the variables in a folder, you
         will want to submit your changes to the Device Server. To do
         this, set the Status variable to 4. If you want to discard the
         changes, set the Status variable to 6.
         4-Indicates that the changes in the container folder are to be
           submitted to the Device Server.
         6-Indicates that the changes in the container folder are to be
           discarded."
      ::= { wlanProfileEntry 2 }

wlanProfileEnable OBJECT-TYPE
    SYNTAX      YesNoValue
    MAX-ACCESS  read-write
    STATUS      current
    DESCRIPTION
        "Only enabled profiles are considered for association with access points."
    ::= { wlanProfileEntry 3 }

wlanProfileConnectPriority OBJECT-TYPE
    SYNTAX      Integer32(1..8)
    MAX-ACCESS  read-write
    STATUS      current
    DESCRIPTION
        "The connect priority which the IOLAN uses when attempting to connect to an access point."
    ::= { wlanProfileEntry 4 }

wlanProfileName OBJECT-TYPE
    SYNTAX      DisplayString(SIZE(0..32))
    MAX-ACCESS  read-write
    STATUS      current
    DESCRIPTION
        "The name for this profile.
         To delete the profile, set this field to blank.
         If blank, this entry is currently unused."
    ::= { wlanProfileEntry 5 }

wlanProfileSsid OBJECT-TYPE
    SYNTAX      DisplayString(SIZE(1..32))
    MAX-ACCESS  read-write
    STATUS      current
    DESCRIPTION
        "The SSID for this profile."
    ::= { wlanProfileEntry 6 }

wlanProfileScanBand OBJECT-TYPE
    SYNTAX      INTEGER {
        bandBoth(1),
        band2g4(2),
        band5g(3)
    }
    MAX-ACCESS  read-write
    STATUS      current
    DESCRIPTION
        "This profile is considered only if the access point is using the selected band.
        
         bandBoth:     either 2.4GHz or 5GHz bands    
         band2g4:      2.4GHz band
         band5g:       5GHz band"
    ::= { wlanProfileEntry 7 }

wlanProfileScanDfs OBJECT-TYPE
    SYNTAX      OnOffValue
    MAX-ACCESS  read-write
    STATUS      current
    DESCRIPTION
        "Enable/disable scanning of DFS channels."
    ::= {wlanProfileEntry 8 }	  

wlanProfileHiddenSsid OBJECT-TYPE
    SYNTAX      YesNoValue
    MAX-ACCESS  read-write
    STATUS      current
    DESCRIPTION
        "Specify whether the access point hides (Yes) or broadcasts (No) the SSID."
    ::= { wlanProfileEntry 9 }

wlanProfileSecurityType OBJECT-TYPE
    SYNTAX      INTEGER {
    	open(1),
    	shared(2),
        wpa2Personal(3),
        wpaPersonal(4),
        wpa2Enterprise(5),
        wpaEnterprise(6),
        ieee8021x(7)
        
    }
    MAX-ACCESS  read-write
    STATUS      current
    DESCRIPTION
        "The security type to use."
    ::= { wlanProfileEntry 10 }

wlanProfileEncryptionType OBJECT-TYPE
    SYNTAX      INTEGER {
        none(1),
        wep(2),
        tkip(3),
        aes(4)
    }
    MAX-ACCESS  read-write
    STATUS      current
    DESCRIPTION
        "The encryption type to use."
    ::= { wlanProfileEntry 11 }

-- Open/Shared

wlanProfileOpenSharedWepKey1 OBJECT-TYPE
    SYNTAX      DisplayString(SIZE(5..26))
    MAX-ACCESS  read-write
    STATUS      current
    DESCRIPTION
        "WEP key 1.
         5 case sensitive characters (wep-40) or
         13 case sensitive characters (wep-104) or
         10 hexadecimal case insensitive characters or
         26 hexadecimal case insensitive characters."
    ::= { wlanProfileEntry 12 }

wlanProfileOpenSharedWepKey2 OBJECT-TYPE
    SYNTAX      DisplayString(SIZE(5..26))
    MAX-ACCESS  read-write
    STATUS      current
    DESCRIPTION
        "WEP key 1.
         5 case sensitive characters (wep-40) or
         13 case sensitive characters (wep-104) or
         10 hexadecimal case insensitive characters or
         26 hexadecimal case insensitive characters."
    ::= { wlanProfileEntry 13 }

wlanProfileOpenSharedWepKey3 OBJECT-TYPE
    SYNTAX      DisplayString(SIZE(5..26))
    MAX-ACCESS  read-write
    STATUS      current
    DESCRIPTION
        "WEP key 1.
         5 case sensitive characters (wep-40) or
         13 case sensitive characters (wep-104) or
         10 hexadecimal case insensitive characters or
         26 hexadecimal case insensitive characters."
    ::= { wlanProfileEntry 14 }

wlanProfileOpenSharedWepKey4 OBJECT-TYPE
    SYNTAX      DisplayString(SIZE(5..26))
    MAX-ACCESS  read-write
    STATUS      current
    DESCRIPTION
        "WEP key 1.
         5 case sensitive characters (wep-40) or
         13 case sensitive characters (wep-104) or
         10 hexadecimal case insensitive characters or
         26 hexadecimal case insensitive characters."
    ::= { wlanProfileEntry 15 }

wlanProfileOpenSharedWepTxKeyIndex OBJECT-TYPE
    SYNTAX      Integer32(1..4)
    MAX-ACCESS  read-write
    STATUS      current
    DESCRIPTION
        "The index of the WEP key to use for encrypting transmitted data."
    ::= { wlanProfileEntry 16}

-- Personal

wlanProfilePersonalSecurityKey OBJECT-TYPE
    SYNTAX      DisplayString(SIZE(8..64))
    MAX-ACCESS  read-write
    STATUS      current
    DESCRIPTION
        "Passphrase/key to use for encrypting the data.
         8-63 case sensitive characters or
         64 hexadecimal characters."
    ::= { wlanProfileEntry 17 }

-- Enterprise

wlanProfileEnterpriseUsername OBJECT-TYPE
    SYNTAX      DisplayString(SIZE(0..254))
    MAX-ACCESS  read-write
    STATUS      current
    DESCRIPTION
        "The username to use for authentication."
    ::= { wlanProfileEntry 18 }

wlanProfileEnterprisePassword OBJECT-TYPE
    SYNTAX      DisplayString(SIZE(0..128))
    MAX-ACCESS  read-write
    STATUS      current
    DESCRIPTION
        "The password to use for authentication."
    ::= { wlanProfileEntry 19 }

wlanProfileEnterpriseValidateCert OBJECT-TYPE
    SYNTAX      OnOffValue
    MAX-ACCESS  read-write
    STATUS      current
    DESCRIPTION
        "Enable/disable validation of the server certificate."
    ::= {wlanProfileEntry 20}	  

wlanProfileEnterpriseAuthMethod OBJECT-TYPE
    SYNTAX      INTEGER {
        eapttls(1),
        peap(2),
        leap(3),
        eaptls(4)
    }
    MAX-ACCESS  read-write
    STATUS      current
    DESCRIPTION
        "Authentication method."
    ::= { wlanProfileEntry 21}

wlanProfileEnterpriseAuthProtocol OBJECT-TYPE
    SYNTAX      INTEGER {
        pap(1),
        chap(2),
        mschap(3),
        mschapv2(4),
        eapmschapv2(5),
        eapmd5(6),
        eapgtc(7)
    }
    MAX-ACCESS  read-write
    STATUS      current
    DESCRIPTION
        "Authentication protocol."
    ::= { wlanProfileEntry 22}

wlanProfileEnterpriseRoamingIdentity OBJECT-TYPE
    SYNTAX      DisplayString(SIZE(0..63))
    MAX-ACCESS  read-write
    STATUS      current
    DESCRIPTION
        "Roaming identity."
    ::= { wlanProfileEntry 23 }

-- 802.1x

wlanProfile8021xUsername OBJECT-TYPE
    SYNTAX      DisplayString(SIZE(0..254))
    MAX-ACCESS  read-write
    STATUS      current
    DESCRIPTION
        "The username to use for authentication."
    ::= { wlanProfileEntry 24 }

wlanProfile8021xPassword OBJECT-TYPE
    SYNTAX      DisplayString(SIZE(0..128))
    MAX-ACCESS  read-write
    STATUS      current
    DESCRIPTION
        "The password to use for authentication."
    ::= { wlanProfileEntry 25 }

wlanProfile8021xValidateCert OBJECT-TYPE
    SYNTAX      OnOffValue
    MAX-ACCESS  read-write
    STATUS      current
    DESCRIPTION
        "Enable/disable validation of the server certificate."
    ::= {wlanProfileEntry 26}	  

wlanProfile8021xAuthMethod OBJECT-TYPE
    SYNTAX      INTEGER {
        eapttls(1),
        peap(2),
        leap(3),
        eaptls(4)
    }
    MAX-ACCESS  read-write
    STATUS      current
    DESCRIPTION
        "Authentication method."
    ::= { wlanProfileEntry 27}

wlanProfile8021xAuthProtocol OBJECT-TYPE
    SYNTAX      INTEGER {
        pap(1),
        chap(2),
        mschap(3),
        mschapv2(4),
        eapmschapv2(5),
        eapmd5(6),
        eapgtc(7)
    }
    MAX-ACCESS  read-write
    STATUS      current
    DESCRIPTION
        "Authentication protocol."
    ::= { wlanProfileEntry 28}

wlanProfile8021xRoamingIdentity OBJECT-TYPE
    SYNTAX      DisplayString(SIZE(0..63))
    MAX-ACCESS  read-write
    STATUS      current
    DESCRIPTION
        "Roaming identity."
    ::= { wlanProfileEntry 29 }

--  wlanProfilesCfg group end


--  wlanStats group start

wlanStatsMode OBJECT-TYPE
    SYNTAX      INTEGER {
        disabled(1),
        client(2),
        softap(3)
    }
    MAX-ACCESS  read-only
    STATUS      current
    DESCRIPTION
        "The WLAN operating mode."
    ::= { wlanStats 1}

wlanStatsConnected OBJECT-TYPE
    SYNTAX      DisplayString
    MAX-ACCESS  read-only
    STATUS      current
    DESCRIPTION
        "Connected status varies depending on operating mode.
        
         Mode
         Disabled: No
         Client:   Yes/No
         Soft-AP:  # of connected clients"
    ::= { wlanStats 2 }

wlanStatsProfile OBJECT-TYPE
    SYNTAX      DisplayString
    MAX-ACCESS  read-only
    STATUS      current
    DESCRIPTION
        "In client mode, the WLAN profile corresponding to the currently connected access point."
    ::= { wlanStats 3 }

wlanStatsSsid OBJECT-TYPE
    SYNTAX      DisplayString
    MAX-ACCESS  read-only
    STATUS      current
    DESCRIPTION
        "In Client mode, this is the SSID of the currently connected access point.
         In Soft-AP mode, this is the SSID of the IOLAN."
    ::= { wlanStats 4 }

wlanStatsBssid OBJECT-TYPE
    SYNTAX      MacAddress
    MAX-ACCESS  read-only
    STATUS      current
    DESCRIPTION
        "In Client mode, this is the BSSID of the currently connected access point.
         In Soft-AP mode, this is the BSSID of the last connected client."
    ::= { wlanStats 5 }

wlanStatsChannel OBJECT-TYPE
    SYNTAX      Integer32
    MAX-ACCESS  read-only
    STATUS      current
    DESCRIPTION
        "The channel currently being used in Client and Soft-AP mode."
    ::= { wlanStats 6 }

wlanStatsRssi OBJECT-TYPE
    SYNTAX      Integer32
    MAX-ACCESS  read-only
    STATUS      current
    DESCRIPTION
        "The power level of the received signal in dBm."
    ::= { wlanStats 7 }

wlanStatsIpAddress OBJECT-TYPE
    SYNTAX      IpAddress
    MAX-ACCESS  read-only
    STATUS      current
    DESCRIPTION
        "The current IP address of the IOLAN's WLAN interface."
    ::= { wlanStats 8 }

wlanStatsTxRate OBJECT-TYPE
    SYNTAX      Integer32
    MAX-ACCESS  read-only
    STATUS      current
    DESCRIPTION
        "The current transmit rate."
    ::= { wlanStats 9 }

wlanStatsRegion OBJECT-TYPE
    SYNTAX      DisplayString
    MAX-ACCESS  read-only
    STATUS      current
    DESCRIPTION
        "The currently configured operating region."
    ::= { wlanStats 10 }

wlanStatsSecurityType OBJECT-TYPE
    SYNTAX      DisplayString
    MAX-ACCESS  read-only
    STATUS      current
    DESCRIPTION
        "The security type used in the current connection."
    ::= { wlanStats 11 }
    
wlanStatsEncryptionType OBJECT-TYPE
    SYNTAX      DisplayString
    MAX-ACCESS  read-only
    STATUS      current
    DESCRIPTION
        "The encryption used in the current connection."
    ::= { wlanStats 12 }

wlanStatsPairwiseCipher OBJECT-TYPE
    SYNTAX      DisplayString
    MAX-ACCESS  read-only
    STATUS      current
    DESCRIPTION
        "The pairwise cipher used in the current connection."
    ::= { wlanStats 13 }

wlanStatsGroupCipher OBJECT-TYPE
    SYNTAX      DisplayString
    MAX-ACCESS  read-only
    STATUS      current
    DESCRIPTION
        "The group cipher used in the current connection."
    ::= { wlanStats 14 }

--  wlanStats group end

-- WLAN info ENDS



-- SSH Server Info

  sftpStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {sftpInfo 1}

  sftpCompression OBJECT-TYPE
      SYNTAX      OnOffValue
      MAX-ACCESS  read-write
      STATUS      current
      DESCRIPTION
              "Requests compression of all data. Compression is desirable
               on modem lines and other slow connections, but will only
               slow down things on fast networks"
      ::= { sftpInfo 2}

  sftpAutoLogin OBJECT-TYPE
      SYNTAX      OnOffValue
      MAX-ACCESS  read-write
      STATUS      current
      DESCRIPTION
              "Creates an automatic SFTP authentication, using the Name and Password values."
      ::= { sftpInfo 3}

  sftpName OBJECT-TYPE
      SYNTAX      DisplayString(SIZE(0..20))
      MAX-ACCESS  read-write
      STATUS      current
      DESCRIPTION
              "The name of the user on the SFTP server."
      ::= { sftpInfo 4}

  sftpPassword OBJECT-TYPE
      SYNTAX      DisplayString(SIZE(0..20))
      MAX-ACCESS  read-write
      STATUS      current
      DESCRIPTION
              "The user's password on the SFTP server."
      ::= { sftpInfo 5}

  sftpHost OBJECT-TYPE
      SYNTAX      DisplayString(SIZE(0..14))
      MAX-ACCESS  read-write
      STATUS      current
      DESCRIPTION
              "The name of the SFTP host."
      ::= { sftpInfo 6}

  sftpTunnelName OBJECT-TYPE
      SYNTAX      DisplayString(SIZE(0..14))
      MAX-ACCESS  read-write
      STATUS      current
      DESCRIPTION
              "The name of the HTTP tunnel associated with this service."
      ::= { sftpInfo 7 }
  
  sftpProtocol OBJECT-TYPE
      SYNTAX      INTEGER {
        ssh1(1),
        ssh2(2),
        sshBoth(3)
      }
      MAX-ACCESS  read-write
      STATUS      current
      DESCRIPTION
              "Specify the SSH client version that will be used
               with the SFTP server."
      ::= { sftpInfo 8}

  sftpRSA OBJECT-TYPE
      SYNTAX      OnOffValue
      MAX-ACCESS  read-write
      STATUS      current
      DESCRIPTION
              "An authentication method used by SSH version 1 and 2.
               Use RSA authentication for the SFTP server."
      ::= { sftpInfo 9}

  sftpDSA OBJECT-TYPE
      SYNTAX      OnOffValue
      MAX-ACCESS  read-write
      STATUS      current
      DESCRIPTION
              "An authentication method used by SSH version 2.
               Use DSA authentication for the SFTP server."
      ::= { sftpInfo 10}

  sftpKeyboard OBJECT-TYPE
      SYNTAX      OnOffValue
      MAX-ACCESS  read-write
      STATUS      current
      DESCRIPTION
              "The user types in a password for authentication."
      ::= { sftpInfo 11}

  sftpCipherSSH1 OBJECT-TYPE
      SYNTAX      INTEGER {
              tripledes(1),
          blowfish(2)
        }
      MAX-ACCESS  read-write
      STATUS      current
      DESCRIPTION
              "Select the encryption method (cipher) that you
               want to use for your SSH version 1 connection:
               3DES or Blowfish"
      ::= { sftpInfo 12}

  sftpFirstSSH2Cipher OBJECT-TYPE
      SYNTAX      INTEGER {
        tripledes(1),
        blowfish(2),
        aes(3),
        cast(4),
        arcfour(5)
      }
      MAX-ACCESS  read-write
      STATUS      current
      DESCRIPTION
              "Select the first priority negotiation for the encryption
               method (ciphers) that the Device Server will use for
               the SSH version 2 connection:
               3DES, Blowfish, AES, CAST, or Arcfour"
      ::= { sftpInfo 13}

  sftpSecondSSH2Cipher OBJECT-TYPE
      SYNTAX      INTEGER {
        none(1),
        tripledes(2),
        blowfish(3),
        aes(4),
        cast(5),
        arcfour(6)
      }
      MAX-ACCESS  read-write
      STATUS      current
      DESCRIPTION
              "Select the second priority negotiation for the encryption
               method (ciphers) that the Device Server will use for
               the SSH version 2 connection:
               None, 3DES, Blowfish, AES, CAST, or Arcfour"
      ::= { sftpInfo 14}

  sftpThirdSSH2Cipher OBJECT-TYPE
      SYNTAX      INTEGER {
        none(1),
        tripledes(2),
        blowfish(3),
        aes(4),
        cast(5),
        arcfour(6)
      }
      MAX-ACCESS  read-write
      STATUS      current
      DESCRIPTION
              "Select the third priority negotiation for the encryption
               method (ciphers) that the Device Server will use for
               the SSH version 2 connection:
               None, 3DES, Blowfish, AES, CAST, or Arcfour"
      ::= { sftpInfo 15}

  sftpFourthSSH2Cipher OBJECT-TYPE
      SYNTAX      INTEGER {
        none(1),
        tripledes(2),
        blowfish(3),
        aes(4),
        cast(5),
        arcfour(6)
      }
      MAX-ACCESS  read-write
      STATUS      current
      DESCRIPTION
              "Select the fourth priority negotiation for the encryption
               method (ciphers) that the Device Server will use for
               the SSH version 2 connection:
               None, 3DES, Blowfish, AES, CAST, or Arcfour"
      ::= { sftpInfo 16}

  sftpFifthSSH2Cipher OBJECT-TYPE
      SYNTAX      INTEGER {
        none(1),
        tripledes(2),
        blowfish(3),
        aes(4),
        cast(5),
        arcfour(6)
      }
      MAX-ACCESS  read-write
      STATUS      current
      DESCRIPTION
              "Select the fifth priority negotiation for the encryption
               method (ciphers) that the Device Server will use for
               the SSH version 2 connection:
               None, 3DES, Blowfish, AES, CAST, or Arcfour"
      ::= { sftpInfo 17}
  

-- wwanInfo BEGINS

wwanCfg                OBJECT IDENTIFIER ::= { wwanInfo 1 }
wwanStats              OBJECT IDENTIFIER ::= { wwanInfo 2 }

--  wwanCfg group start
wwanGlobalStatus OBJECT-TYPE
    SYNTAX      ContainerStatus
    MAX-ACCESS  read-write
    STATUS      current
    DESCRIPTION
        "When you perform a GET on this variable, one of
         the following values will be returned:
         1-Indicates that the container folder is active with no changes.
         2-Indicates that the container folder is active with change(s).
         Once you have completed setting the variables in a folder, you
         will want to submit your changes to the Device Server. To do
         this, set the Status variable to 4. If you want to discard the
         changes, set the Status variable to 6.
         4-Indicates that the changes in the container folder are to be
           submitted to the Device Server.
         6-Indicates that the changes in the container folder are to be
           discarded."
    ::= { wwanCfg 1 }

wwanEnable OBJECT-TYPE
	SYNTAX      YesNoValue
    MAX-ACCESS  read-write
    STATUS      current
    DESCRIPTION
        "Enable/disable WWAN"
    ::= { wwanCfg 2 }

wwanApn OBJECT-TYPE
    SYNTAX      DisplayString(SIZE(1..100))
    MAX-ACCESS  read-write
    STATUS      current
    DESCRIPTION
        "The APN required by your service provider to 
         access the network."
    ::= { wwanCfg 3 }

wwanAuthentication OBJECT-TYPE
    SYNTAX      INTEGER {
        authNone(1),
        authPap(2),
        authChap(3)
    }
    MAX-ACCESS  read-write
    STATUS      current
    DESCRIPTION
        "The authentication method required by your service provider."
    ::= { wwanCfg 4 }

wwanUsername OBJECT-TYPE
    SYNTAX      DisplayString(SIZE(0..127))
    MAX-ACCESS  read-write
    STATUS      current
    DESCRIPTION
        "The username required by your service provider if the authentication 
         method is PAP or CHAP."
    ::= { wwanCfg 5 }

wwanPassword OBJECT-TYPE
    SYNTAX      DisplayString(SIZE(0..127))
    MAX-ACCESS  read-write
    STATUS      current
    DESCRIPTION
        "The password required by your service provider if the authentication 
         method is PAP or CHAP."
    ::= { wwanCfg 6 }

wwanPin OBJECT-TYPE
    SYNTAX      DisplayString(SIZE(0..8))
    MAX-ACCESS  read-write
    STATUS      current
    DESCRIPTION
        "The PIN required to unlock a PIN protected SIM."
    ::= { wwanCfg 7 }

wwanRadioAccessTechnology OBJECT-TYPE
    SYNTAX      INTEGER {
        ratAuto(1),
        ratLte(2),
        rat3g(3),
        rat2g(4)
    }
    MAX-ACCESS  read-write
    STATUS      current
    DESCRIPTION
        "The radio access technology of the network to connect to."
    ::= { wwanCfg 8 }
    
wwanAutoDns OBJECT-TYPE
    SYNTAX      OnOffValue
    MAX-ACCESS  read-write
    STATUS      current
    DESCRIPTION
        "If enabled, the DNS server IP address will be retrieved automatically from the network."
    ::= { wwanCfg 9 }

--  wwanCfg group end

--  wwanStats group start
wwanStatsModemModel OBJECT-TYPE
    SYNTAX      DisplayString
    MAX-ACCESS  read-only
    STATUS      current
    DESCRIPTION
        "The modem model."
    ::= { wwanStats 1 }

wwanStatsModemFirmwareVersion OBJECT-TYPE
    SYNTAX      DisplayString
    MAX-ACCESS  read-only
    STATUS      current
    DESCRIPTION
        "The modem firmware version."
    ::= { wwanStats 2 }

wwanStatsIMEI OBJECT-TYPE
    SYNTAX      DisplayString
    MAX-ACCESS  read-only
    STATUS      current
    DESCRIPTION
        "The identifier of the modem."
    ::= { wwanStats 3 }

wwanStatsICCID OBJECT-TYPE
    SYNTAX      DisplayString
    MAX-ACCESS  read-only
    STATUS      current
    DESCRIPTION
        "The identifier of the actual SIM card itself."
    ::= { wwanStats 4 }

wwanStatsIMSI OBJECT-TYPE
    SYNTAX      DisplayString
    MAX-ACCESS  read-only
    STATUS      current
    DESCRIPTION
        "A unique identifier that defines a subscriber in the
         wireless world, including the country and mobile network to which the subscriber belongs."
    ::= { wwanStats 5 }

wwanStatsPinRetryCounter OBJECT-TYPE
    SYNTAX      Integer32
    MAX-ACCESS  read-only
    STATUS      current
    DESCRIPTION
        "The number of retries remaining for the SIM PIN."
    ::= { wwanStats 6 }

wwanStatsNetworkType OBJECT-TYPE
    SYNTAX      DisplayString
    MAX-ACCESS  read-only
    STATUS      current
    DESCRIPTION
        "The radio access technology used to connect to the network."
    ::= { wwanStats 7 }

wwanStatsNetworkStatus OBJECT-TYPE
    SYNTAX      DisplayString
    MAX-ACCESS  read-only
    STATUS      current
    DESCRIPTION
        "The network connection status."
    ::= { wwanStats 8 }

wwanStatsNetworkName OBJECT-TYPE
    SYNTAX      DisplayString
    MAX-ACCESS  read-only
    STATUS      current
    DESCRIPTION
        "The name of the connected network."
    ::= { wwanStats 9 }

wwanStatsAPN OBJECT-TYPE
    SYNTAX      DisplayString
    MAX-ACCESS  read-only
    STATUS      current
    DESCRIPTION
        "The APN used to connect to the network."
    ::= { wwanStats 10 }

wwanStatsSignalStrength OBJECT-TYPE
    SYNTAX      Integer32
    MAX-ACCESS  read-only
    STATUS      current
    DESCRIPTION
        "The strength of the network signal."
    ::= { wwanStats 11 }

wwanStatsIpAddress OBJECT-TYPE
    SYNTAX      IpAddress
    MAX-ACCESS  read-only
    STATUS      current
    DESCRIPTION
        "The current IP address of the IOLAN's WWAN interface."
    ::= { wwanStats 12 }
    
wwanStatsRxBytes OBJECT-TYPE
      SYNTAX      Counter32
      MAX-ACCESS  read-only
      STATUS      current
      DESCRIPTION
        "RX byte count."
      ::= { wwanStats 13 }
      
wwanStatsTxBytes OBJECT-TYPE
      SYNTAX      Counter32
      MAX-ACCESS  read-only
      STATUS      current
      DESCRIPTION
        "TX byte count."
      ::= { wwanStats 14 }
      
--  wwanStats group end

-- wwanInfo ENDS

-- sfpInfo
-- sfpModuleTable
--
  sfpModuleTable OBJECT-TYPE
    SYNTAX		SEQUENCE OF SfpModuleEntry
    MAX-ACCESS	not-accessible
    STATUS		current
    DESCRIPTION
        "Table of SFP information for Optical Transceivers"
    ::= { sfpInfo 1 }

    sfpModuleEntry OBJECT-TYPE
        SYNTAX      SfpModuleEntry
        MAX-ACCESS  not-accessible
        STATUS      current
        DESCRIPTION
            "Entries of the table, each relating to a separate SFP module."
        INDEX   { sfpInterfaceIndex }
        	::= { sfpModuleTable 1 }

  SfpModuleEntry ::=
    SEQUENCE {
         sfpInterfaceIndex 			GenericTableIndex,
         sfpStatus 					BITS,
         sfpVendorSerialNumber 		DisplayString,
         sfpVendorName 				DisplayString,
         sfpVendorPartNumber 		DisplayString,
         sfpConnectorType 			INTEGER,
         sfpNominalBitRate 			Unsigned32,
         sfpLinkReach9125 			Integer32,
         sfpLinkReach50125 			Integer32,
         sfpLinkReach625125 		Integer32,
         sfpReachCopper 			Integer32,
         sfpFiberWaveLength 		Unsigned32,
         sfpDmiCurrentTempState 	INTEGER,
         sfpDmiRealTimeTemp 		DisplayString,
         sfpDmiHighTempWarn 		DisplayString,
         sfpDmiHighTempAlarm 		DisplayString,
         sfpDmiLowTempWarn 			DisplayString,
         sfpDmiLowTempAlarm 		DisplayString,
         sfpDmiCurrentVoltState 	INTEGER,
         sfpDmiRealTimeVolt 		DisplayString,
         sfpDmiHighVoltWarn 		DisplayString,
         sfpDmiHighVoltAlarm 		DisplayString,
         sfpDmiLowVoltWarn 			DisplayString,
         sfpDmiLowVoltAlarm 		DisplayString,
         sfpDmiCurrentTxBiasState 	INTEGER,
         sfpDmiRealTimeTxBias 		DisplayString,
         sfpDmiHighTxBiasWarn 		DisplayString,
         sfpDmiHighTxBiasAlarm 		DisplayString,
         sfpDmiLowTxBiasWarn 		DisplayString,
         sfpDmiLowTxBiasAlarm 		DisplayString,
         sfpDmiCurrentTxPowerState 	INTEGER,
         sfpDmiRealTimeTxPower 		DisplayString,
         sfpDmiHighTxPowerWarn 		DisplayString,
         sfpDmiHighTxPowerAlarm 	DisplayString,
         sfpDmiLowTxPowerWarn 		DisplayString,
         sfpDmiLowTxPowerAlarm 		DisplayString,
         sfpDmiCurrentRxPowerState	INTEGER,
         sfpDmiRealTimeRxPower 		DisplayString,
         sfpDmiHighRxPowerWarn 		DisplayString,
         sfpDmiHighRxPowerAlarm 	DisplayString,
         sfpDmiLowRxPowerWarn 		DisplayString,
         sfpDmiLowRxPowerAlarm 		DisplayString
    }

	sfpInterfaceIndex OBJECT-TYPE
	  SYNTAX      GenericTableIndex
	  MAX-ACCESS not-accessible
	  STATUS      current
	  DESCRIPTION
			  "The Ethernet interface number."
	  ::= { sfpModuleEntry 1 }

	sfpStatus	OBJECT-TYPE
	  SYNTAX		BITS {
		  sfpModuleInserted(24),
		  sfpCommFailed(25),
		  sfpDmiSupported(26)
	  }
	  MAX-ACCESS	read-only
	  STATUS		current
	  DESCRIPTION
		  "This object identifies the status of the SFP module. If sfpCommFailed
		   value is set then the rest of the data in this entry is invalid
		   0x80 - sfpModuleInserted
		   0x40 - sfpCommFailed
		   0x20 - sfpDmiSupported"
	  ::= { sfpModuleEntry 2 }
	
	sfpVendorSerialNumber	OBJECT-TYPE
	  SYNTAX	DisplayString (SIZE(0..32))
	  MAX-ACCESS	read-only
	  STATUS		current
	  DESCRIPTION
		  "This object identifies the SFP's vendor serial number. "
	  ::= { sfpModuleEntry 3 }
	
	sfpVendorName		OBJECT-TYPE
	  SYNTAX	DisplayString (SIZE(0..32))
	  MAX-ACCESS	read-only
	  STATUS		current
	  DESCRIPTION
		  "This object identifies the SFP's vendor company name. "
	  ::= { sfpModuleEntry 4 }
	
	sfpVendorPartNumber	OBJECT-TYPE
	  SYNTAX	DisplayString (SIZE(0..32))
	  MAX-ACCESS	read-only
	  STATUS		current
	  DESCRIPTION
		  "This object identifies the SFP's vendor part number. "
	  ::= { sfpModuleEntry 5 }
	
	sfpConnectorType	OBJECT-TYPE
	  SYNTAX		INTEGER {
		  unknownUnspecified(0),
		  sc(1),
		  fiberChannelStyle1Copper(2),
		  fiberChannelStyle2Copper(3),
		  bncTnc(4),
		  fiberChannelCoaxHeader(5),
		  fiberJack(6),
		  lc(7),
		  mtrj(8),
		  mu(9),
		  sg(10),
		  opticalPigtail(11),
		  MpoParallelOptic(12);
		  hssdcII(32),
		  copperPigtail(33),
		  rj45(34)
	  }
	  MAX-ACCESS	read-only
	  STATUS		current
	  DESCRIPTION
		  "This object identifies the SFP connector type."
	  ::= { sfpModuleEntry 6 }
	
	sfpNominalBitRate	OBJECT-TYPE
	  SYNTAX		Unsigned32
	  MAX-ACCESS	read-only
	  STATUS		current
	  DESCRIPTION
		  "This object identifies the SFP nominal bit rate of fiber
		   interface, in megabits per second."
	  ::= { sfpModuleEntry 7 }
	
	sfpLinkReach9125	OBJECT-TYPE
	  SYNTAX		Integer32
	  MAX-ACCESS	read-only
	  STATUS		current
	  DESCRIPTION
		  "This object identifies the SFP DMI maximum length in meters of media
		   supported by the fiber transceiver for 9 micron (125 micron jacket)
		   single-mode fiber. "
	  ::= { sfpModuleEntry 8 }
	
	sfpLinkReach50125	OBJECT-TYPE
	  SYNTAX		Integer32
	  MAX-ACCESS	read-only
	  STATUS		current
	  DESCRIPTION
		  "This object identifies the SFP maximum length in meters of media
		   supported by the fiber transceiver for 50 micron (125 micron jacket)
		   multi-mode fiber."
	  ::= { sfpModuleEntry 9 }
	
	sfpLinkReach625125	OBJECT-TYPE
	  SYNTAX        Integer32
	  MAX-ACCESS    read-only
	  STATUS        current
	  DESCRIPTION
		  "This object identifies the SFP maximum length in meters of media
		   supported by the fiber transceiver for 62.5 micron (125 micron jacket)
		   multi-mode fiber."
	  ::= { sfpModuleEntry 10 }
	
	sfpReachCopper     OBJECT-TYPE
	  SYNTAX     Integer32
	  MAX-ACCESS read-only
	  STATUS     current
	  DESCRIPTION
		  "This object identifies the maximum length in meters that is 
		   supported by the SFP/XFP interface using copper cable."
	  ::= { sfpModuleEntry 11 }
	
	sfpFiberWaveLength	OBJECT-TYPE
	  SYNTAX        Unsigned32
	  MAX-ACCESS    read-only
	  STATUS    current
	  DESCRIPTION
		  "This object identifies the  wavelength of the fiber interface's
		   optical transceiver, in nanometers."
	  ::= { sfpModuleEntry 12 }
	
	sfpDmiCurrentTempState	OBJECT-TYPE
	  SYNTAX INTEGER {
		  invalid(0),
		  notSupported(1),
		  normal(2),
		  highWarn(3),
		  highAlarm(4),
		  lowWarn(5),
		  lowAlarm(6)
	  }
	  MAX-ACCESS    read-only
	  STATUS        current
	  DESCRIPTION
		  "This object identifies the current alarm status for SFP DMI internally
		   measured temperature. "
	  ::= { sfpModuleEntry 13 }
	
	sfpDmiRealTimeTemp	OBJECT-TYPE
	  SYNTAX	DisplayString (SIZE(0..32))
	  MAX-ACCESS	read-only
	  STATUS		current
	  DESCRIPTION
		  "This object identifies the SFP DMI real time temperature."
	  ::= { sfpModuleEntry 14 }
	
	sfpDmiHighTempWarn	OBJECT-TYPE
	  SYNTAX	DisplayString (SIZE(0..32))
	  MAX-ACCESS	read-only
	  STATUS		current
	  DESCRIPTION
		  "This object identifies the SFP DMI high temperature warning threshold.
		   The value displayed will be either Celsius or Fahrenheit based on your
		   current regional display settings. "
	  ::= { sfpModuleEntry 15 }
	
	sfpDmiHighTempAlarm	OBJECT-TYPE
	  SYNTAX	DisplayString (SIZE(0..32))
	  MAX-ACCESS	read-only
	  STATUS		current
	  DESCRIPTION
		  "This object identifies the SFP DMI high temperature warning threshold."
	  ::= { sfpModuleEntry 16 }
	
	sfpDmiLowTempWarn	OBJECT-TYPE
	  SYNTAX	DisplayString (SIZE(0..32))
	  MAX-ACCESS	read-only
	  STATUS		current
	  DESCRIPTION
		  "This object identifies the SFP DMI high temperature warning threshold."
	  ::= { sfpModuleEntry 17 }
	
	sfpDmiLowTempAlarm	OBJECT-TYPE
	  SYNTAX	DisplayString (SIZE(0..32))
	  MAX-ACCESS	read-only
	  STATUS		current
	  DESCRIPTION
		  "This object identifies the SFP DMI high temperature warning threshold."
	  ::= { sfpModuleEntry 18 }
	
	sfpDmiCurrentVoltState	OBJECT-TYPE
	  SYNTAX INTEGER {
		  invalid(0),
		  notSupported(1),
		  normal(2),
		  highWarn(3),
		  highAlarm(4),
		  lowWarn(5),
		  lowAlarm(6)
	  }
	  MAX-ACCESS	read-only
	  STATUS		current
	  DESCRIPTION
		  "This object identifies current alarm status for SFP DMI internally
		   measured voltage. "
	  ::= { sfpModuleEntry 19 }
	
	sfpDmiRealTimeVolt	OBJECT-TYPE
	  SYNTAX	DisplayString (SIZE(0..32))
	  MAX-ACCESS	read-only
	  STATUS		current
	  DESCRIPTION
		  "This object identifies the SFP DMI real time voltage in Volts. "
	  ::= { sfpModuleEntry 20 }
	
	sfpDmiHighVoltWarn	OBJECT-TYPE
	  SYNTAX	DisplayString (SIZE(0..32))
	  MAX-ACCESS	read-only
	  STATUS		current
	  DESCRIPTION
		  "This object identifies the SFP DMI high voltage warning threshold in
		   Volts "
	  ::= { sfpModuleEntry 21 }
	
	sfpDmiHighVoltAlarm	OBJECT-TYPE
	  SYNTAX	DisplayString (SIZE(0..32))
	  MAX-ACCESS	read-only
	  STATUS		current
	  DESCRIPTION
		  "This object identifies the SFP DMI high voltage warning threshold in
		   Volts "
	  ::= { sfpModuleEntry 22 }
	
	sfpDmiLowVoltWarn	OBJECT-TYPE
	  SYNTAX	DisplayString (SIZE(0..32))
	  MAX-ACCESS	read-only
	  STATUS		current
	  DESCRIPTION
		  "This object identifies the SFP DMI high voltage warning threshold in
		   Volts"
	  ::= { sfpModuleEntry 23 }
	
	sfpDmiLowVoltAlarm	OBJECT-TYPE
	  SYNTAX	DisplayString (SIZE(0..32))
	  MAX-ACCESS	read-only
	  STATUS		current
	  DESCRIPTION
		  "This object identifies the SFP DMI high voltage warning threshold in
		   Volts"
	  ::= { sfpModuleEntry 24 }
	
	sfpDmiCurrentTxBiasState	OBJECT-TYPE
	  SYNTAX		INTEGER {
		  invalid(0),
		  notSupported(1),
		  normal(2),
		  highWarn(3),
		  highAlarm(4),
		  lowWarn(5),
		  lowAlarm(6)
	  }
	  MAX-ACCESS	read-only
	  STATUS		current
	  DESCRIPTION
		  "This object identifies current alarm status for SFP DMI internally
		   measured transmit bias current in milliamps. "
	  ::= { sfpModuleEntry 25 }
	
	sfpDmiRealTimeTxBias	OBJECT-TYPE
	  SYNTAX	DisplayString (SIZE(0..32))
	  MAX-ACCESS	read-only
	  STATUS		current
	  DESCRIPTION
		  "This object identifies the SFP DMI high TX Bias current in milliamps. "
	  ::= { sfpModuleEntry 26 }
	
	sfpDmiHighTxBiasWarn	OBJECT-TYPE
	  SYNTAX	DisplayString (SIZE(0..32))
	  MAX-ACCESS	read-only
	  STATUS		current
	  DESCRIPTION
		  "This object identifies the SFP DMI high TX Bias current warning
		   threshold in milliamps."
	  ::= { sfpModuleEntry 27 }
	
	sfpDmiHighTxBiasAlarm	OBJECT-TYPE
	  SYNTAX	DisplayString (SIZE(0..32))
	  MAX-ACCESS	read-only
	  STATUS		current
	  DESCRIPTION
		  "This object identifies the SFP DMI high TX Bias current alarm
		   threshold in milliamps."
	  ::= { sfpModuleEntry 28 }
	
	sfpDmiLowTxBiasWarn	OBJECT-TYPE
	  SYNTAX	DisplayString (SIZE(0..32))
	  MAX-ACCESS	read-only
	  STATUS		current
	  DESCRIPTION
		  "This object identifies the SFP DMI low TX Bias current warning
		   threshold in milliamps."
	  ::= { sfpModuleEntry 29 }
	
	sfpDmiLowTxBiasAlarm	OBJECT-TYPE
	  SYNTAX	DisplayString (SIZE(0..32))
	  MAX-ACCESS	read-only
	  STATUS		current
	  DESCRIPTION
		  "This object identifies the SFP DMI low TX Bias current alarm
		   threshold in milliamps."
	  ::= { sfpModuleEntry 30 }
	
	sfpDmiCurrentTxPowerState	OBJECT-TYPE
	  SYNTAX		INTEGER {
		  invalid(0),
		  notSupported(1),
		  normal(2),
		  highWarn(3),
		  highAlarm(4),
		  lowWarn(5),
		  lowAlarm(6)
	  }
	  MAX-ACCESS	read-only
	  STATUS		current
	  DESCRIPTION
		  "This object identifies current alarm status for SFP DMI internally
		   measured transmit power. "
	  ::= { sfpModuleEntry 31 }
	
	sfpDmiRealTimeTxPower	OBJECT-TYPE
	  SYNTAX	DisplayString (SIZE(0..32))
	  MAX-ACCESS	read-only
	  STATUS		current
	  DESCRIPTION
		  "This object identifies the SFP DMI real time TX output power.
		   The value displayed will be either millwatts or Dbm based on your
		   current regional display settings. "
	
	  ::= { sfpModuleEntry 32 }
	
	sfpDmiHighTxPowerWarn	OBJECT-TYPE
	  SYNTAX	DisplayString (SIZE(0..32))
	  MAX-ACCESS	read-only
	  STATUS		current
	  DESCRIPTION
		  "This object identifies the SFP DMI high TX output power warning
		   threshold. The value displayed will be either millwatts or Dbm based
		   on your current regional display settings. "
	
	  ::= { sfpModuleEntry 33 }
	
	sfpDmiHighTxPowerAlarm	OBJECT-TYPE
	  SYNTAX	DisplayString (SIZE(0..32))
	  MAX-ACCESS	read-only
	  STATUS		current
	  DESCRIPTION
		  "This object identifies the SFP DMI high TX output power alarm
		   threshold. The value displayed will be either millwatts or Dbm based
		   on your current regional display settings. "
	  ::= { sfpModuleEntry 34 }
	
	sfpDmiLowTxPowerWarn	OBJECT-TYPE
	  SYNTAX	DisplayString (SIZE(0..32))
	  MAX-ACCESS	read-only
	  STATUS		current
	  DESCRIPTION
		  "This object identifies the SFP DMI low TX output power warning
		   threshold. The value displayed will be either millwatts or Dbm based
		   on your current regional display settings. "
	  ::= { sfpModuleEntry 35 }
	
	sfpDmiLowTxPowerAlarm	OBJECT-TYPE
	  SYNTAX	DisplayString (SIZE(0..32))
	  MAX-ACCESS	read-only
	  STATUS		current
	  DESCRIPTION
		  "This object identifies the SFP DMI low TX output power alarm
		   threshold. The value displayed will be either millwatts or Dbm based
		   on your current regional display settings. "
	  ::= { sfpModuleEntry 36 }
	
	sfpDmiCurrentRxPowerState	OBJECT-TYPE
	  SYNTAX		INTEGER {
		  invalid(0),
		  notSupported(1),
		  normal(2),
		  highWarn(3),
		  highAlarm(4),
		  lowWarn(5),
		  lowAlarm(6)
	  }
	  MAX-ACCESS	read-only
	  STATUS		current
	  DESCRIPTION
		  "This object identifies current alarm status for SFP DMI internally
		   measured receive power. "
	  ::= { sfpModuleEntry 37 }
	
	sfpDmiRealTimeRxPower	OBJECT-TYPE
	  SYNTAX	DisplayString (SIZE(0..32))
	  MAX-ACCESS	read-only
	  STATUS		current
	  DESCRIPTION
		  "This object identifies the SFP DMI real time RX received optical power.
		   The value displayed will be either millwatts or Dbm based
		   on your current regional display settings. "
	  ::= { sfpModuleEntry 38 }
	
	sfpDmiHighRxPowerWarn	OBJECT-TYPE
	  SYNTAX	DisplayString (SIZE(0..32))
	  MAX-ACCESS	read-only
	  STATUS		current
	  DESCRIPTION
		  "This object identifies the SFP DMI high RX received optical warning
		   threshold. The value displayed will be either millwatts or Dbm based
		   on your current regional display settings. "
	  ::= { sfpModuleEntry 39 }
	
	sfpDmiHighRxPowerAlarm	OBJECT-TYPE
	  SYNTAX	DisplayString (SIZE(0..32))
	  MAX-ACCESS	read-only
	  STATUS		current
	  DESCRIPTION
		  "This object identifies the SFP DMI high RX received optical alarm
		   threshold. The value displayed will be either millwatts or Dbm based
		   on your current regional display settings. "
	  ::= { sfpModuleEntry 40 }
	
	sfpDmiLowRxPowerWarn	OBJECT-TYPE
	  SYNTAX	DisplayString (SIZE(0..32))
	  MAX-ACCESS	read-only
	  STATUS		current
	  DESCRIPTION
		  "This object identifies the SFP DMI low RX received optical warning
		   threshold. The value displayed will be either millwatts or Dbm based
		   on your current regional display settings. "
	  ::= { sfpModuleEntry 41 }
	
	sfpDmiLowRxPowerAlarm	OBJECT-TYPE
	  SYNTAX	DisplayString (SIZE(0..32))
	  MAX-ACCESS	read-only
	  STATUS		current
	  DESCRIPTION
		  "This object identifies the SFP DMI low RX received optical alarm
		   threshold. The value displayed will be either millwatts or Dbm based
		   on your current regional display settings. "
	  ::= { sfpModuleEntry 42 }

  
--end sfpInfo  

-- frontPanelInfo
   fpStatus OBJECT-TYPE
      SYNTAX      ContainerStatus
      MAX-ACCESS  read-write
      STATUS      current
      DESCRIPTION
              "When you perform a GET on this variable, one of
               the following values will be returned:
               1-Indicates that the container folder is active with no changes.
               2-Indicates that the container folder is active with change(s).
               Once you have completed setting the variables in a folder, you
               will want to submit your changes to the Device Server. To do
               this, set the Status variable to 4. If you want to discard the
               changes, set the Status variable to 6.
               4-Indicates that the changes in the container folder are to be
                 submitted to the Device Server.
               6-Indicates that the changes in the container folder are to be
                 discarded."
      ::= {frontPanelInfo 1}
  
  fpLcdAutoScrollEnable OBJECT-TYPE
      SYNTAX      INTEGER {
        disable(0),
        enable(1)
      }
      MAX-ACCESS  read-write
      STATUS      current
      DESCRIPTION
              "Defines whether the front panel LCD will auto-scroll the specified screens"
      ::= { frontPanelInfo 2}

  fpLcdScrollDelay OBJECT-TYPE
      SYNTAX      Integer32 (1..60)
      MAX-ACCESS  read-write
      STATUS      current
      DESCRIPTION
              "Defines the time between screens when auto-scroll is enabled."
      ::= { frontPanelInfo 3}

  fpLcdIdleTimeout OBJECT-TYPE
      SYNTAX      Integer32 (60..600)
      MAX-ACCESS  read-write
      STATUS      current
      DESCRIPTION
              "Defines the time after a keypad key is pressed before the 
              auto-scroll will resume."
      ::= { frontPanelInfo 4}

  fpCustomTextLine1 OBJECT-TYPE
      SYNTAX      DisplayString(SIZE(0..18))
      MAX-ACCESS  read-write
      STATUS      current
      DESCRIPTION
              "Defines line 1 of the custom text screen." 
      ::= { frontPanelInfo 5}

  fpCustomTextLine2 OBJECT-TYPE
      SYNTAX      DisplayString(SIZE(0..18))
      MAX-ACCESS  read-write
      STATUS      current
      DESCRIPTION
              "Defines line 2 of the custom text screen." 
      ::= { frontPanelInfo 6}
  
  fpKeypadLock OBJECT-TYPE
      SYNTAX      INTEGER {
        unlocked(0),
        locked(1)
      }
      MAX-ACCESS  read-write
      STATUS      current
      DESCRIPTION
              "Defines whether the front panel keypad is locked for editing functions"
      ::= { frontPanelInfo 7}
      
  fpKeypadPin OBJECT-TYPE
      SYNTAX      INTEGER {
        pin-disabled(0),
        pin-enabled(1)
      }
      MAX-ACCESS  read-write
      STATUS      current
      DESCRIPTION
              "Request a Pin in order to have access to config and admin menus"
      ::= { frontPanelInfo 8}     
  
  fpKeypadPinNumber OBJECT-TYPE
      SYNTAX      DisplayString(SIZE(0..6))
      MAX-ACCESS  read-write
      STATUS      current
      DESCRIPTION
              "Specifies the 6 numeric character pin which is required to 
              reset the front panel config to factory default." 
      ::= { frontPanelInfo 9}
  
  fpLcdScreenOrder	 OBJECT IDENTIFIER ::= { frontPanelInfo 10 }

  fpLcdScreenOrder1 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 1."
	  ::= { fpLcdScreenOrder 1}
  
  fpLcdScreenOrder2 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 2."
	  ::= { fpLcdScreenOrder 2}
      
  fpLcdScreenOrder3 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 3."
	  ::= { fpLcdScreenOrder 3}
      
  fpLcdScreenOrder4 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 4."
	  ::= { fpLcdScreenOrder 4}
      
  fpLcdScreenOrder5 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 5."
	  ::= { fpLcdScreenOrder 5}
      
  fpLcdScreenOrder6 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 6."
	  ::= { fpLcdScreenOrder 6}
      
  fpLcdScreenOrder7 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 7."
	  ::= { fpLcdScreenOrder 7}
      
  fpLcdScreenOrder8 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 8."
	  ::= { fpLcdScreenOrder 8}
      
  fpLcdScreenOrder9 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 9."
	  ::= { fpLcdScreenOrder 9}
      
  fpLcdScreenOrder10 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 10."
	  ::= { fpLcdScreenOrder 10}
      
fpLcdScreenOrder11 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 11."
	  ::= { fpLcdScreenOrder 11}
      
      
  fpLcdScreenOrder12 OBJECT-TYPE
	  SYNTAX      INTEGER {
	  	disabled(-1),
	  	ipv4-ethernet-address(0),
	  	ipv6-ethernet-address(1),
	  	hardware-mac-address(2),
		serial-numbers(3),
		console(4),
		release(5),
		temperature(6),
		custom-text(7),
		port-connections(8),
		wlan-connection-information(9),
		wwan-connection-information(10),
		server-info(11)
	  }
	  MAX-ACCESS  read-write
	  STATUS      current
	  DESCRIPTION
			  "Defines the which screen is displayed in order 12."
	  ::= { fpLcdScreenOrder 12}
  
-- end of sdsMIBObjects


-- sdsMIB Notifications 
  
sdsMIBNotificationsPrefix OBJECT IDENTIFIER
        ::= { sdsMIBNotifications 0 }

     
sdsMIBIoDigitalInputAlarmSensor NOTIFICATION-TYPE 
  OBJECTS {  ioDigitalStatusState }
  STATUS  current
  DESCRIPTION
            "A sdsMIBIoDigitalInputAlarmSensor trap signifies that the Digital
             I/O channel input sensor alarm has triggered."
  ::= { sdsMIBNotificationsPrefix 1 }

sdsMIBIoLineInputDSRAlarm  NOTIFICATION-TYPE 
  OBJECTS {  ioLineSignalStatusState }
  STATUS  current
  DESCRIPTION
            "A sdsMIBIoLineInputDSRAlarm trap signifies that the Serial
             line DSR input alarm has triggered."
  ::= { sdsMIBNotificationsPrefix 2 }

sdsMIBIoLineInputDCDAlarm NOTIFICATION-TYPE 
  OBJECTS {  ioLineSignalStatusState }
  STATUS  current
  DESCRIPTION
            "A sdsMIBIoLineInputDCDAlarm trap signifies that the Serial
             line DCD input alarm has triggered."
  ::= { sdsMIBNotificationsPrefix 3 }

sdsMIBIoLineInputCTSAlarm NOTIFICATION-TYPE 
  OBJECTS {  ioLineSignalStatusState }
  STATUS  current
  DESCRIPTION
            "A sdsMIBIoLineInputCTSAlarm trap signifies that the Serial
             line CTS input alarm has triggered."
  ::= { sdsMIBNotificationsPrefix 4 }

sdsMIBIoAnalogInputAlarmSeverityLevel1 NOTIFICATION-TYPE 
  OBJECTS {  ioAnalogStatusValue }
  STATUS  current
  DESCRIPTION
            "A sdsMIBIoAnalogInputAlarmSeverityLevel1 trap signifies that the Analog
             I/O channel input alarm has triggered at severity level 1."
  ::= { sdsMIBNotificationsPrefix 5 }

sdsMIBIoAnalogInputAlarmSeverityLevel2 NOTIFICATION-TYPE 
  OBJECTS {  ioAnalogStatusValue }
  STATUS  current
  DESCRIPTION
            "A sdsMIBIoAnalogInputAlarmSeverityLevel2 trap signifies that the Analog
             I/O channel input alarm has triggered at severity level 2."
  ::= { sdsMIBNotificationsPrefix 6 }

sdsMIBIoAnalogInputAlarmSeverityLevel3 NOTIFICATION-TYPE 
  OBJECTS {  ioAnalogStatusValue }
  STATUS  current
  DESCRIPTION
            "A sdsMIBIoAnalogInputAlarmSeverityLevel3 trap signifies that the Analog
             I/O channel input alarm has triggered at severity level 3."
  ::= { sdsMIBNotificationsPrefix 7 }
sdsMIBIoAnalogInputAlarmSeverityLevel4 NOTIFICATION-TYPE 
  OBJECTS {  ioAnalogStatusValue }
  STATUS  current
  DESCRIPTION
            "A sdsMIBIoAnalogInputAlarmSeverityLevel4 trap signifies that the Analog
             I/O channel input alarm has triggered at severity level 4."
  ::= { sdsMIBNotificationsPrefix 8 }

sdsMIBIoAnalogInputAlarmSeverityLevel5 NOTIFICATION-TYPE 
  OBJECTS {  ioAnalogStatusValue }
  STATUS  current
  DESCRIPTION
            "A sdsMIBIoAnalogInputAlarmSeverityLevel5 trap signifies that the Analog
             I/O channel input alarm has triggered at severity level 5."
  ::= { sdsMIBNotificationsPrefix 9 }

sdsMIBIoDigitalInputAlarmClear NOTIFICATION-TYPE 
  OBJECTS {  ioDigitalStatusState }
  STATUS  current
  DESCRIPTION
            "A sdsMIBIoDigitalInputAlarmClear trap signifies that the Digital
             I/O channel input sensor alarm has cleared."
  ::= { sdsMIBNotificationsPrefix 10 }

sdsMIBIoLineInputDSRAlarmClear NOTIFICATION-TYPE 
  OBJECTS {  ioLineSignalStatusState }
  STATUS  current
  DESCRIPTION
            "A sdsMIBIoLineInputDSRAlarmClear trap signifies that the Serial
             line DSR input alarm has cleared."
  ::= { sdsMIBNotificationsPrefix 11 }

sdsMIBIoLineInputDCDAlarmClear NOTIFICATION-TYPE 
  OBJECTS {  ioLineSignalStatusState }
  STATUS  current
  DESCRIPTION
            "A sdsMIBIoLineInputDCDAlarmClear trap signifies that the Serial
             line DCD input alarm has cleared."
  ::= { sdsMIBNotificationsPrefix 12 }

sdsMIBIoLineInputCTSAlarmClear NOTIFICATION-TYPE 
  OBJECTS {  ioLineSignalStatusState }
  STATUS  current
  DESCRIPTION
            "A sdsMIBIoLineInputCTSAlarmClear trap signifies that the Serial
             line CTS input alarm has cleared."
  ::= { sdsMIBNotificationsPrefix 13 }
     
sdsMIBIoAnalogInputAlarmSeverityLevel1Clear NOTIFICATION-TYPE 
  OBJECTS {  ioAnalogStatusValue }
  STATUS  current
  DESCRIPTION
            "A sdsMIBIoAnalogInputAlarmSeverityLevel1Clear trap signifies that the Analog
             I/O channel input alarm at severity level 1 has cleared."
  ::= { sdsMIBNotificationsPrefix 14 }

sdsMIBIoAnalogInputAlarmSeverityLevel2Clear NOTIFICATION-TYPE 
  OBJECTS {  ioAnalogStatusValue }
  STATUS  current
  DESCRIPTION
            "A sdsMIBIoAnalogInputAlarmSeverityLevel2Clear trap signifies that the Analog
             I/O channel input alarm at severity level 2 has cleared."
  ::= { sdsMIBNotificationsPrefix 15 }

sdsMIBIoAnalogInputAlarmSeverityLevel3Clear NOTIFICATION-TYPE 
  OBJECTS {  ioAnalogStatusValue }
  STATUS  current
  DESCRIPTION
            "A sdsMIBIoAnalogInputAlarmSeverityLevel3Clear trap signifies that the Analog
             I/O channel input alarm at severity level 3 has cleared."
  ::= { sdsMIBNotificationsPrefix 16 }

sdsMIBIoAnalogInputAlarmSeverityLevel4Clear NOTIFICATION-TYPE 
  OBJECTS {  ioAnalogStatusValue }
  STATUS  current
  DESCRIPTION
            "A sdsMIBIoAnalogInputAlarmSeverityLevel4Clear trap signifies that the Analog
             I/O channel input alarm at severity level 4 has cleared."
  ::= { sdsMIBNotificationsPrefix 17 }

sdsMIBIoAnalogInputAlarmSeverityLevel5Clear NOTIFICATION-TYPE 
  OBJECTS {  ioAnalogStatusValue }
  STATUS  current
  DESCRIPTION
            "A sdsMIBIoAnalogInputAlarmSeverityLevel5Clear trap signifies that the Analog
             I/O channel input alarm at severity level 5 has cleared."
  ::= { sdsMIBNotificationsPrefix 18 }
  
    
sdsMIBEthernetLinkDown NOTIFICATION-TYPE 
  OBJECTS { ethStatsName,ethStatsStatus }
  STATUS  current
  DESCRIPTION
            "A sdsMIBEthernetLinkDown trap signifies that the sending SNMP application 
             entity recognizes a failure in one of the communications links 
             represented in the agent's configuration."
  ::= { sdsMIBNotificationsPrefix 19 }

sdsMIBEthernetLinkUp NOTIFICATION-TYPE
  OBJECTS { ethStatsName,ethStatsStatus }
  STATUS  current
  DESCRIPTION
            "A sdsMIBEthernetLinkUp trap signifies that the sending SNMP application 
             entity has detected that one of the communications links has 
             transitioned out of the down state."
  ::= { sdsMIBNotificationsPrefix 20 }


  -- sdsMIB conformance information

  sdsMIBCompliances OBJECT IDENTIFIER 
     ::= {   sdsMIBConformance 1 }
  sdsMIBGroups       OBJECT IDENTIFIER 
     ::= { sdsMIBConformance 2 }

-- compliance statements

sdsMIBCompliance MODULE-COMPLIANCE
    STATUS       current
    DESCRIPTION
               "The compliance statement for sdsMIB which implement
                the Perle IOLAN SDS, SCS and STS MIB."
    MODULE    -- this module
    MANDATORY-GROUPS { 
       sdsMIBMainGroup,
       sdsMIBNotificationsGroup
    }

    ::= {  sdsMIBCompliances  1 }

    
-- units of conformance 

sdsMIBMainGroup OBJECT-GROUP
  OBJECTS {
     adminFunction,adminLastFunction,adminStatus,adminSystemDate,
     adminSystemTime,adminKillLine,adminGetClusteredSlavePortNames,adminPowerOn,
     adminPowerOff,adminPowerBoot,adminPowerReset,adminPowerStatus,
     adminIpsec,adminPowerMonitorResetRebootInfo,adminPowerMonitorLastRebootTime,
     adminPowerMonitorNumberOfReboots,adminPowerMonitorStatus,
     adminPowerMonitorOff,adminPowerMonitorOn,adminSerialNumbers,
  
     serverStatus,serverName,serverDomainName,serverIPaddress,
     serverSubnetBits,serverPortBuffering,serverViewPortBufferString,
     serverTimeStamping,serverSessionEscapeString,serverNFSHostName,
     serverNFSDirectory,serverNFSEncryption,serverPortMenuString,
     serverBreakEnabled,serverBanner,serverSecurity,serverPromptWithName,
     serverPasswordLimit,serverOemLogin,serverBypassPassword,
     serverSingleTelnet,serverFlushOnClose,serverPrimaryAuthMethod,
     serverSecondaryAuthMethod,serverEthernetSpeedDuplex,serverTFTPRetry,
     serverTFTPTimeOut,serverEnableGuestLogin,serverSecondaryIPaddress,
     serverSecondarySubnetBits,serverEthSecondarySpeedDuplex,
     serverDHCPUpdateDNSPrimary,serverPowerManagementMenuString,
     serverActiveStandbyEnabled,serverActiveStandbyMiimon,
     serverActiveStandbyUpdelay,serverDropSessionDetectionTime,
     serverAutoObtainDNS,serverAutoObtainWINS,serverAutoObtainGW,
     serverAlwaysAttemptSecond,serverDHCPUpdateDNSSecondary,
     serverDomainPrefixPrimary,serverDomainPrefixSecondary,
     serverPortBufferSyslog,serverPortBufferKeyStroke,serverIpsecUseNat,
     serverAutoObtainDNSV6,serverAuthenticateAdminlocal,serverDisplayMotdWeb,
     serverGenericWebLoginScreen,serverNfsHostTunnel,
     serverPortBufferSyslogLevel,serverEasyPortWebClient,
     serverDataLoggingBufferSize, serverDataLoggingOptions, serverKeepAliveRetries, 
     serverKeepAliveTimeout, serverEth0MTU, serverEth1MTU, 
     serverTFTPHost, serverTFTPTunnelName,
     serverIPaddress3, serverSubnetBits3, serverDHCPUpdateDNS3, serverDomainPrefix3,
     serverEth3MTU, serverEth1MediaType, serverEth1Sgmii, serverEth2MediaType, serverEth2Sgmii,
     
     
     hostStatus,hostName,hostIpAddr,fqdn,
     
     userStatus,userName,userService,userLanguage,userLevel,userHotKeyPrefix,
     userPhoneNumber,userCallBack,userIdleTimer,userSessionTimer,userIpHost,
     userTelnetPort,userSSHPort,userTcpClearPort,userFramedIp,userSubnetBits,
     userIpv6InterfaceIdentifier,userFramedMtu,userFramedCompression,
     userRouting,userPortConnected,userSessionTime,userIdleTime,
     userAllowAccessClusterPorts,userHost,userTunnel,
     
     portAccessStatus,portRWAccessAllowed,portRIAccessAllowed,
     portROAccessAllowed,
     
     userSessionStatus,userSessionType,userSessionAuto,userSessionTelnetPort,
     userSessionTelnetHost,userSessionTelnetTermType,userSessionTelnetEcho,
     userSessionTelnetMapnl,userSessionTelnetMode,userSessionTelnetInterrupt,
     userSessionTelnetQuit,userSessionTelnetEOF,userSessionTelnetErase,
     userSessionTelnetEchoCC,userSessionTelnetBreak,userSessionSSHPort,
     userSessionSSHHost,userSessionSSHTermType,userSessionSSHVerbose,
     userSessionSSHCompression,userSessionSSHAutoLogin,userSessionSSHName,
     userSessionSSHProtocol,userSessionSSHRSA,userSessionSSHDSA,
     userSessionSSHKeyboard,userSessionSSHCipherSSH1,
     userSessionSSHFirstSSH2Cipher,userSessionSSHSecondSSH2Cipher,
     userSessionSSHThirdSSH2Cipher,userSessionSSHFourthSSH2Cipher,
     userSessionSSHFifthSSH2Cipher,userSessionRloginHost,userSessionRloginTermType,
     userSessionTelnetTunnelName,userSessionSSHTunnelName,userSessionRloginTunnelName,
     userSessionStrictHostKeyChecking,
     userSessionSSHSixthSSH2Cipher,userSessionSSHSeventhSSH2Cipher,userSessionSSHEighthSSH2Cipher,

     portStatus,portName,portService,portDial,portModem,portPhone,
     portTermType,portPages,portPreDefinedUser,portDSPort,portIdleTimer,
     portSessionTimer,portSecurity,portBreak,portInboundFlowControl,
     portOutboundFlowControl,portInitialMode,portReset,portKeepalive,
     portMapCR,portMOTD,portHotKeyPrefix,portLock,portEnable,portMultiSession,
     portDialRetries,portDialTimeout,portInternetAddress,portRawOption,
     portDirectTrigger,portDataLogging,portSacSupport,portHdwStatus,
     portHdwInterface,portHdwSpeed,portHdwDataBits,portHdwParity,
     portHdwStopBits,portHdwFlowControl,portHdwMonitorDSR,portHdwMonitorDCD,
     portHdwDuplex,portHdwTXDriverControl,portHdwEchoSuppression,portHdwUART,
     portHdwIRQ,portHdwTxBytes,portHdwRxBytes,portHdwFrameErrs,
     portHdwParityErrs,portHdwBreaks,portHdwOverruns,portHdwRTS,portHdwCTS,
     portHdwDTR,portHdwDSR,portHdwCD,portHdwRI,portSoftTermination,
     portHdwCustomSpeed,portRawTunnelName,portBreakDelay,portBreakLength,
     portConnectStringDelay,portConnectTerminateString,portConnectInitiateString, 
     portSendName,portHdwDiscardCharactersRecievedWithErrors,              
     portHdwRtsToggle,portHdwRtsInitialDelay,portHdwRtsFinalDelay,portHdwDataEquipment,portHdwSlot,
     
     portTelnetStatus,portTelnetPort,portTelnetHost,portTelnetTermType,
     portTelnetEcho,portTelnetMapnl,portTelnetMode,portTelnetInterrupt,
     portTelnetQuit,portTelnetEOF,portTelnetErase,portTelnetEchoCC,
     portTelnetBreak,portTelnetTunnelName,
     
     portSSHStatus,portSSHPort,portSSHHost,portSSHTermType,
     portSSHVerbose,portSSHCompression,portSSHAutoLogin,portSSHName,
     portSSHProtocol,portSSHRSA,portSSHDSA,portSSHKeyboard,portSSHCipherSSH1,
     portSSHFirstSSH2Cipher,portSSHSecondSSH2Cipher,portSSHThirdSSH2Cipher,
     portSSHFourthSSH2Cipher,portSSHFifthSSH2Cipher,portSSHTunnelName,
     portSSHStrictHostKeyChecking,portSSHSixthSSH2Cipher,
     portSSHSeventhSSH2Cipher,portSSHEighthSSH2Cipher

     portPPPStatus,portPPPLocalIpAddr,portPPPRemoteIpAddr,portPPPSubnetBits,
     portPPPIpV6LocalIpAddr,portPPPIpV6RemoteIpAddr,portPPPAccm,portPPPMru,
     portPPPSecurity,portPPPUser,portPPPRemoteUser,portPPPACComp,
     portPPPProtoComp,portPPPVJComp,portPPPMagicNegotiation,
     portPPPIPAddrNegotiation,portPPPCRTimeout,portPPPTRTimeout,
     portPPPCRRetry,portPPPTRRetry,portPPPNakRetry,portPPPAuthTimeout,
     portPPPRoamingCallback,portPPPChallengInterval,portPPPRouting,
     portPPPDynamicDNSEnabled,portPPPDynamicDNSHostname,
     portPPPDynamicDNSUserName,portPPPDynamicDNSPassword,
     portPPPDynamicDNSStatusString,portPPPMSDirectConnection,
     portPPPIPv6Prefix,portPPPIPv6PrefixBits,portPPPEchoTimeout,portPPPEchoRetry,

     portSlipStatus,portSLIPLocalIpAddress,portSLIPRemoteIpAddress,
     portSLIPSubnetBits,portSLIPMtu,portSLIPVJComp,portSLIPRouting,
     
     portUDPStatus,portUDPStartAddress,portUDPEndAddress,portUDPPort,
     portUDPDirection,portUDPOption,portUDPTunnelName,

     portVmodemStatus,portVmodemHost,portVmodemPort,portVmodemSuccessString,
     portVmodemFailureString,portVmodemSuppress,portVmodemStyle,
     portVmodemResponseDelay,portVmodemEcho,portVmodemMode,portVmodemDCD,
     portVmodemRTS,portVmodemDTR,portVmodemInitString,portVmodemTunnelName,

     portRawStatus,portRawPort,portRawHost,

     portBidirStatus,portBidirPort,portBidirHost,portBidirTunnelName,

     portRloginStatus,portRloginHost,portRloginTermType,portRloginTunnelName,

     portEmailStatus,portEmailActive,portEmailLevel,portEmailTo,portEmailFrom,
     portEmailReply,portEmailSubject, portEmailUseDefaultLevel, 

     portSSLStatus,portSSLEnabled,portSSLuseServer,portSSLVersion,portSSLType,
     portSSLVerifyPeerCertificate,portSSLCountry,portSSLStateProv,
     portSSLLocality,portSSLOrganisation,portSSLOrganisationUnit,
     portSSLCommonName,portSSLEmail,portEmailUseDefaultTo,portEmailUseDefaultFrom,
     portEmailUseDefaultReply,portEmailUseDefaultSubject,

     portSSLCipherStatus,portSSLCipherEncryption,portSSLCipherKeySizeMin,
     portSSLCipherKeySizeMax,portSSLCipherKeyExchange,portSSLCipherHMAC,

     portPacketForwardingStatus,portPacketForwardingPacketSize,portPacketForwardingIdleTime,
     portPacketForwardingForceTransmitTime,portPacketForwardingEnableSOF1,portPacketForwardingSOF1,
     portPacketForwardingEnableSOF2,portPacketForwardingSOF2,portPacketForwardingStartFrameTransmit,
     portPacketForwardingEnableEOF1,portPacketForwardingEOF1,portPacketForwardingEnableEOF2,
     portPacketForwardingEOF2,portPacketForwardingEnableEndTrigger1,
     portPacketForwardingEndTrigger1,portPacketForwardingEnableEndTrigger2,
     portPacketForwardingEndTrigger2,portPacketForwardingForwardingRule,
     portPacketForwardingPacketIdleTime,portPacketForwardingForwardMode,

     portPowerManagementMonitorEnableEmail,
     portPowerManagementMonitorEnableConsoleMsg,portPowerManagementMonitorDelay,
     portPowerManagementMonitorEnableDelay,portPowerManagementMonitorRetries,
     portPowerManagementMonitorTimeout,portPowerManagementMonitorInterval,
     portPowerManagementMonitorHost,
      
     portTunnelStatus,portTunnelPort,portTunnelHost,portTunnelHttpTunnelName,

     portMODBUSSlaveStatus,portMODBUSSlaveMode,portMODBUSSlaveCRLF,portMODBUSSlaveUIDRange,

     portMODBUSMasterStatus,portMODBUSMasterMode,portMODBUSMasterCRLF,

     portMODBUSMasterMappingStatus, portMODBUSMasterMappingRemoteIP,
     portMODBUSMasterMappingTransportType,portMODBUSMasterMappingPortNumber,
     portMODBUSMasterMappingUIDStart,portMODBUSMasterMappingUIDEnd,
     portMODBUSMasterMappingUIDRangeMode,portMODBUSMasterMappingTunnelName,

     portCustomAppStatus,portCustomAppCommand,

     portTrueportServiceStatus,portTrueportServicePort,
     portTrueportServiceHost,portTrueportServiceClientInitiated,
     portTrueportServiceActiveSignal,portTrueportServiceTunnelName,

     portPowerManagementStatus,portPowerManagementName,portPowerManagementModel,

     portPowerManagementPlugStatus,portPowerManagementPlugName,
     portPowerManagementPlugPowerUpInterval,portPowerManagementPlugDefaultState,
     portPowerManagementDSLine,

     portMultihostStatus,portMultihostMode,

     portMultihostOutboundStatus,portMultihostOutboundHostID,
     portMultihostOutboundTcpPort,portMultihostOutboundTunnel,

     modemStatus,modemName,modemInitialisation,

     serviceStatus,serviceDHCP,serviceRouteD,serviceTelnetD,serviceSSHD,
     serviceHTTPD,serviceSnmpD,serviceSPCD,serviceSNTP,serviceHTTPSD,
     serviceSyslog,serviceDeviceManagerD,serviceMODBUSD,
     serviceSecondaryDHCP,serviceIPSEC, serviceIncomingPings,

     trueportStatus,trueport50,trueport75,trueport110,trueport134,trueport150,
     trueport200,trueport300,trueport600,trueport1200,trueport1800,
     trueport2400,trueport4800,trueport9600,trueport19200,trueport38400,
     trueportCustom50,trueportCustom75,trueportCustom110,trueportCustom134,
     trueportCustom150,trueportCustom200,trueportCustom300,trueportCustom600,
     trueportCustom1200,trueportCustom1800,trueportCustom2400,
     trueportCustom4800,trueportCustom9600,trueportCustom19200,
     trueportCustom38400,

     radiusStatus,radiusPrimaryAuthHost,radiusSecondaryAuthHost,
     radiusAuthenticationPort,radiusAccountingEnabled,radiusPrimaryAcctHost,
     radiusSecondaryAcctHost,radiusAccountingPort,radiusAcctAuth,
     radiusRetryLimit,radiusTimeout,radiusNasIdentifier,radiusNasIpAddress,
     radiusNasSpecifyIpAddress,radiusNasIpv6Address,
     radiusNasSpecifyIpv6Address,radiusSecondaryAcctTunnel,radiusPrimaryAcctTunnel,
     radiusSecondaryAuthTunnel,radiusPrimaryAuthTunnel,

     kerberosStatus,kerberosRealm,kerberosDomain,kerberosPort,
     
     ldapStatus,ldapHost,ldapPort,ldapBase,ldapEnableTLS,ldapTLSPort,
     ldapHostTunnel,ldapClientPassword,ldapClientAppendBase,ldapClientName,
     ldapClientAuth,ldapPasswordEncryption,ldapUID,

     tacacsStatus,tacacsPrimaryHost,tacacsSecondaryHost,tacacsPort,
     tacacsAccounting,tacacsAccountingPrimaryHost,
     tacacsAccountingSecondaryHost,tacacsAccountingPort,tacacsAuthorization,
     tacacsAccountingSecondaryTunnel,tacacsAccountingPrimaryTunnel,
     tacacsSecondaryTunnel,tacacsPrimaryTunnel,tacacsAlternateServiceNames,
     
     securidStatus,securidMasterHost,securidSlaveHost,securidPort,securidType,
     securidLegacy,securidSlaveTunnel,securidMasterTunnel,

     nisStatus,nisDomain,nisPrimaryHost,nisSecondaryHost,nisSecondaryTunnel,
     nisPrimaryTunnel,
     
     sshServerStatus,sshServerRSA,sshServerDSA,sshServerKeyboard,
     sshServer3Des,sshServerBlowfish,sshServerAES,sshServerCAST,
     sshServerArcfour,sshServerVerbose,sshServerCompression,
     sshServerBreakString,sshServerSSH1,sshServerPassword,sshServerLoginTimeout,
     sshServerAESctr,sshServerAESgcm,sshServerChaCha20Poly1305,
     
     defUserStatus,defUserService,defUserLanguage,defUserLevel,
     defUserHotKeyPrefix,defUserPhoneNumber,defUserCallBack,
     defUserIdleTimer,defUserSessionTimer,defUserIpHost,defUserTelnetPort,
     defUserSSHPort,defUserTcpClearPort,defUserFramedIp,defUserSubnetBits,
     defUserIpv6InterfaceId,defUserFramedMtu,defUserFramedCompression,
     defUserRouting,defUserAllowAccessClusterPorts,defUserHost,
     
     defUserPortAccessStatus,defUserPortRWAccessAllowed,
     defUserPortRIAccessAllowed,defUserPortROAccessAllowed,
     
     snmpStatus,snmpContact,snmpLocation,snmpReadOnlyUser,snmpReadWriteUser,
     
     snmpCommunityStatus,snmpCommunityName,snmpCommunityIpAddress,
     snmpCommunityPermission,
     
     snmpTrapStatus,snmpTrapName,snmpTrapIpAddress,snmpTrapTunnelName,
     snmpTrapVersion, snmpTrapType, snmpTrapEnable,
     snmpReadOnlySecurityLevel,snmpReadOnlyAuthAlgorithm,snmpReadOnlyAuthPasswd,
     snmpReadOnlyPrivacyAlgorithm,snmpReadOnlyPrivacyPasswd,
     snmpReadWriteSecurityLevel,snmpReadWriteAuthAlgorithm,
     snmpReadWriteAuthPasswd,snmpReadWritePrivacyAlgorithm,
     snmpReadWritePrivacyPasswd,snmpTrapUser,snmpTrapSecurityLevel,snmpTrapAuthAlgorithm,
     snmpTrapAuthPasswd,snmpTrapPrivacyAlgorithm,snmpTrapPrivacyPasswd,
     snmpEngineIdString,snmpEngineId,snmpInformTimeout,snmpInformRetries,
     
     dnsStatus,dnsIpAddress,dnsActive,
     
     winsStatus,winsIpAddress,winsActive,
     
     gatewayStatus,gatewayHost,gatewayType,gatewayIpAddress,gatewaySubnetBits,
     gatewayInterface,
     
     syslogStatus,syslogPrimaryHost,syslogSecondaryHost,syslogLevel,
     syslogPrimaryTunnel,syslogSecondaryTunnel,
     
     emailStatus,emailActive,emailLevel,emailTo,emailFrom,emailSMTPHost,
     emailReply,emailSubject,
     
     emailSMTPHostTunnel,emailSMTPDomain,emailSMTPTcpPort,emailSMTPValidatePeerCertificate,
     emailSMTPEncryption,emailSMTPPassword,emailSMTPUsername,

     ripStatus,ripMode,ripAuthentication,
     
     ripKeyStatus,ripKeyId,ripKeyStartDate,ripKeyStartTime,ripKeyEndDate,
     ripKeyEndTime,
     
     timeStatus,timeZoneName,timeOffset,timeSummerName,timeSummerOffset,
     timeSummerMode,timeSummerRecStartMonth,timeSummerRecStartWeek,
     timeSummerRecStartDay,timeSummerRecStartHour,timeSummerRecStartMin,
     
     timeSummerRecEndMonth,timeSummerRecEndWeek,timeSummerRecEndDay,
     timeSummerRecEndHour,timeSummerRecEndMin,timeSummerFixStartMonth,
     timeSummerFixStartDay,timeSummerFixStartHour,timeSummerFixStartMinute,
     timeSummerFixEndMonth,timeSummerFixEndDay,timeSummerFixEndHour,
     timeSummerFixEndMinute,timeSntpMode,timeSntpVersion,timeSntpHost1,
     timeSntpHost2,timeSntpTunnelName1,timeSntpTunnelName2, 
     serverSntpServerAuthentication, serverSntpKeyID,
     
     fileStatus,fileFirmwareHost,fileFirmwareName,fileConfigurationHost,
     fileConfigurationName,fileMOTDHost,fileMOTDName,fileMOTDTunnel,
     
     ethStatsName, ethStatsMacAddress,
     ethStatsStatus,ethStatsBroadcast,ethStatsDebug,ethStatsLoopback,
     ethStatsPointtoPoint,ethStatsNoTrailers,ethStatsRunning,ethStatsNoArp,
     ethStatsPromiscuous,ethStatsRxMulticast,ethStatsMasterLoadBalancer,
     ethStatsSlaveLoadBalancer,ethStatsMulticast,ethStatsSetMedia,
     ethStatsAutoMedia,ethStatsDynamic,ethStatsLocalAddress,
     ethStatsSubnetMask,ethStatsBroadcastAddress,ethStatsMtu,ethStatsTxQLen,
     ethStatsRxBytes,ethStatsTxBytes,ethStatsRxPackets,ethStatsTxPackets,
     ethStatsRxErrors,ethStatsTxPktErrors,ethStatsRxDroppedPkts,
     ethStatsTxDroppedPkts,ethStatsRxOverruns,ethStatsTxOverruns,
     ethStatsRxFrameErrs,ethStatsTxCarrierErrs,ethStatsCollisions,
     
     sntpStatsAddress,sntpStatsLastUpdate,sntpStatsLeapIndicator,
     sntpStatsVersion,sntpStatsMode,sntpStatsStratum,sntpStatsRefId,
     sntpStatsOffset,
     
     ripTableIpAddr,ripTableLastUpdate,ripTableVersion,ripTableAuthType,
     ripTableSequence,ripTableBadPackets,ripTableBadRoutes,
     
     tcpConnLocalAddress,tcpConnLocalPort,tcpConnRemoteAddress,
     tcpConnRemotePort,tcpConnTxQueueBytes,tcpConnRxQueueBytes,tcpConnState,
     
     udpConnLocalAddress,udpConnLocalPort,udpConnRemoteAddress,
     udpConnRemotePort,udpConnTxQueueBytes,udpConnRxQueueBytes,udpConnState,
     
     ipV6StatsRxTotalPkts,ipV6StatsRxHdrErrors,ipV6StatsRxTooBigErrors,
     ipV6StatsRxNoRoutes,ipV6StatsRxAddrErrors,ipV6StatsRxUnknownProtos,
     ipV6StatsRxTruncatedPkts,ipV6StatsRxDiscards,ipV6StatsRxDelivers,
     ipV6StatsRxMcastPkts,ipV6StatsTxForwDatagrams,ipV6StatsTxRequests,
     ipV6StatsTxDiscards,ipV6StatsTxNoRoutes,ipV6StatsTxMcastPkts,
     ipV6StatsReasmTimeout,ipV6StatsReasmReqds,ipV6StatsReasmOKs,
     ipV6StatsReasmFails,ipV6StatsFragOKs,ipV6StatsFragFails,
     ipV6StatsFragCreates,
     
     icmpV6TxMsgs,icmpV6TxErrors,icmpV6TxDestUnreachs,icmpV6TxPktTooBigs,
     icmpV6TxTimeExcds,icmpV6TxParmProblems,icmpV6TxEchos,icmpV6TxEchoReplies,
     icmpV6TxGroupMembQueries,icmpV6TxGroupMembResponses,
     icmpV6TxGroupMembReductions,icmpV6TxRouterSolicits,
     icmpV6TxRouterAdvertisements,icmpV6TxNeighborSolicits,
     icmpV6TxNeighborAdvertisements,icmpV6TxRedirects,icmpV6RxMsgs,
     icmpV6RxDestUnreachs,icmpV6RxPktTooBigs,icmpV6RxTimeExcds,
     icmpV6RxParmProblems,icmpV6RxEchoReplies,icmpV6RxRouterSolicits,
     icmpV6RxNeighborSolicits,icmpV6RxNeighborAdvertisements,
     icmpV6RxRedirects,icmpV6RxGroupMembResponses,icmpV6RxGroupMembReductions,
     
     udpV6RxDatagrams,udpV6noPorts,udpV6RxErrors,udpV6TxDatagrams,

     tcpConnv6LocalAddress,tcpConnv6LocalPort,tcpConnv6RemoteAddress,
     tcpConnv6RemotePort,tcpConnv6TxQueueBytes,tcpConnv6RxQueueBytes,
     tcpConnv6State,
     
     udpConnv6LocalAddress,udpConnv6LocalPort,udpConnv6RemoteAddress,
     udpConnv6RemotePort,udpConnv6TxQueueBytes,udpConnv6RxQueueBytes,
     udpConnv6State,
     
     routev6Destination,routev6PrefixBits,routev6Gateway,routev6Metric,
     routev6Flags,routev6Interface,
     
     ripv6TableIpAddr,ripv6TableLastUpdate,ripv6TableBadPackets,
     ripv6TableBadRoutes,
     
     interfacev6Name,interfacev6Address,interfacev6PrefixBits,
     interfacev6Scope,

     sslServerStatus,sslVersion,sslType,sslVerifyPeerCertificate,sslCountry,
     sslStateProv,sslLocality,sslOrganisation,sslOrganisationUnit,
     sslCommonName,sslEmail,

     sslCipherStatus,sslCipherEncryption,sslCipherKeySizeMin,
     sslCipherKeySizeMax,sslCipherKeyExchange,sslCipherHMAC,
     
     consoleStatus,consoleSpeed,consoleFlowControl,consoleMediaType,consoleMediaType,
     
     modbusGatewayStatus,modbusGatewayConnIdleTimeout,modbusGatewayException,
     modbusGatewayCharacterTimeout,modbusGatewayMessageTimeout,modbusGatewayPortNumber,
     modbusGatewayUIDAddressMode,modbusGatewayRemappedUID,modbusGatewayBroadcast,
     modbusGatewayNextRequestDelay,modbusGatewayQueuing,modbusGatewaySSL,
     
     modbusSlaveTCPStatsSerialMode,modbusSlaveTCPStatsSerialFrameErrors,
     
     modbusSlaveTCPStatsGatewayRemoteIP,modbusSlaveTCPStatsGatewayUID,
     modbusSlaveTCPStatsGatewayRemotePortNumber,modbusSlaveTCPStatsGatewayCommands,
     modbusSlaveTCPStatsGatewayResponses,modbusSlaveTCPStatsGatewayExceptions,
     modbusSlaveTCPStatsGatewayFrameErrors,

     modbusMasterTCPStatsSerialMode, modbusMasterTCPStatsSerialFrameErrors,
     
     modbusMasterTCPStatsGatewayRemoteIP,modbusMasterTCPStatsGatewayUID,
     modbusMasterTCPStatsGatewayRemotePortNumber,
     modbusMasterTCPStatsGatewayCommands,modbusMasterTCPStatsGatewayResponses,
     modbusMasterTCPStatsGatewayExceptions,modbusMasterTCPStatsGatewayFrameErrors,
     
     modbusSlaveUDPStatsSerialMode,modbusSlaveUDPStatsSerialFrameErrors,
     modbusSlaveUDPStatsGatewayRemoteIP,modbusSlaveUDPStatsGatewayUID,
     modbusSlaveUDPStatsGatewayRemotePortNumber,modbusSlaveUDPStatsGatewayCommands,
     
     modbusSlaveUDPStatsGatewayResponses,modbusSlaveUDPStatsGatewayExceptions,
     modbusSlaveUDPStatsGatewayFrameErrors,modbusMasterUDPStatsSerialMode,
     modbusMasterUDPStatsSerialFrameErrors,modbusMasterUDPStatsGatewayRemoteIP,
     modbusMasterUDPStatsGatewayUID,modbusMasterUDPStatsGatewayRemotePortNumber,
     modbusMasterUDPStatsGatewayCommands,modbusMasterUDPStatsGatewayResponses,
     modbusMasterUDPStatsGatewayExceptions,modbusMasterUDPStatsGatewayFrameErrors,

     ioModbusSlaveStatsServiceMode,ioModbusSlaveStatsUid,
     ioModbusSlaveStatsCommands,ioModbusSlaveStatsResponses,
     ioModbusSlaveStatsExceptions,

     customAppServerStatus,customAppServerCommand,

     ioGlobalCfgStatus,ioTemperatureScale,ioFailsafeEnable,ioFailsafeTimeout,
     ioModbusEnable,ioModbusUid,ioUdpEnable,ioUdpBroadcastInterval,
     ioUdpEntryEnable,ioUdpEntryStartAddress,ioUdpEntryEndAddress,
     ioUdpEntryPort,ioUdpEntryTunnelName, ioTrueportEnable,
     ioTrueportTcpListenPort, ioTrueportSslEnable,
     
     ioAnalogCfgStatus,ioAnalogCfgEnable,ioAnalogCfgDescription,
     ioAnalogCfgType,ioAnalogCfgRtdRange,ioAnalogCfgThermRange,
     ioAnalogCfgCurrentRange,ioAnalogCfgVoltageRange,ioAnalogCfgAlarmTrigger,
     ioAnalogCfgAlarmClearMode,ioAnalogCfgAlarmEnable,
     ioAnalogCfgAlarmTriggerLevel,ioAnalogCfgAlarmClearLevel,
     ioAnalogCfgAlarmEmail,ioAnalogCfgAlarmSyslog,ioAnalogCfgAlarmSNMP,
     
     ioDigitalCfgStatus,ioDigitalCfgResourceType,ioDigitalCfgEnable,
     ioDigitalCfgDescription,ioDigitalInputCfgLatch,
     ioDigitalInputCfgInvertSignal,ioDigitalInputCfgAlarmTrigger,
     ioDigitalInputCfgAlarmClear,ioDigitalInputCfgAlarmEmail,
     ioDigitalInputCfgAlarmSyslog,ioDigitalInputCfgAlarmSNMP,
     ioDigitalOutputCfgType,ioDigitalOutputCfgMode,
     ioDigitalOutputCfgPulseMode,ioDigitalOutputCfgPulseCount,
     ioDigitalOutputCfgInactiveSignalWidth,ioDigitalOutputCfgActiveSignalWidth,
     ioDigitalOutputCfgDelay,ioDigitalOutputCfgFailsafe,

     ioDigitalExtCfgStatus,ioDigitalExtCfgEnable,ioDigitalExtCfgConnMethod,ioDigitalExtCfgHost,
     ioDigitalExtCfgPort,ioDigitalExtCfgLinkChannel,ioDigitalExtCfgKeepalive,ioDigitalExtCfgMultiHost, ioDigitalExtCfgTunnelName,

     ioDigitalMultihostStatus,ioDigitalMultihostMode,

     ioDigitalMultihostOutboundStatus,ioDigitalMultihostOutboundHostID,ioDigitalMultihostOutboundTcpPort,ioDigitalMultihostOutboundTunnel,

     ioDigitalSSLStatus,ioDigitalSSLEnabled,ioDigitalSSLuseServer,ioDigitalSSLVersion,ioDigitalSSLType,
     ioDigitalSSLVerifyPeerCertificate,ioDigitalSSLCountry,ioDigitalSSLStateProv,ioDigitalSSLLocality,
     ioDigitalSSLOrganisation,ioDigitalSSLOrganisationUnit,ioDigitalSSLCommonName,ioDigitalSSLEmail,
     
     ioDigitalSSLCipherStatus,ioDigitalSSLCipherEncryption,ioDigitalSSLCipherKeySizeMin,
     ioDigitalSSLCipherKeySizeMax,ioDigitalSSLCipherKeyExchange,ioDigitalSSLCipherHMAC,
     
     ioRelayCfgStatus,ioRelayCfgEnable,ioRelayCfgDescription,ioRelayCfgMode,
     ioRelayCfgPulseMode,ioRelayCfgPulseCount,ioRelayCfgInactiveSignalWidth,
     ioRelayCfgActiveSignalWidth,ioRelayCfgDelay,ioRelayCfgFailsafe,
     
     ioRelayExtCfgStatus,ioRelayExtCfgEnable,ioRelayExtCfgConnMethod,
     ioRelayExtCfgHost,ioRelayExtCfgPort,ioRelayExtCfgLinkChannel,
     ioRelayExtCfgKeepalive,ioRelayExtCfgMultiHost, ioRelayExtCfgTunnelName,
     
     ioRelayMultihostStatus,ioRelayMultihostMode,
     
     ioRelayMultihostOutboundStatus,ioRelayMultihostOutboundHostID,
     ioRelayMultihostOutboundTcpPort, ioRelayMultihostOutboundTunnel,
     
     ioRelaySSLStatus,ioRelaySSLEnabled,ioRelaySSLuseServer,ioRelaySSLVersion,
     ioRelaySSLType,ioRelaySSLVerifyPeerCertificate,ioRelaySSLCountry,
     ioRelaySSLStateProv,ioRelaySSLLocality,ioRelaySSLOrganisation,
     ioRelaySSLOrganisationUnit,ioRelaySSLCommonName,ioRelaySSLEmail,
     
     ioRelaySSLCipherStatus,ioRelaySSLCipherEncryption,ioRelaySSLCipherKeySizeMin,
     ioRelaySSLCipherKeySizeMax,ioRelaySSLCipherKeyExchange,ioRelaySSLCipherHMAC,
     
     ioLineSignalCfgStatus,ioLineSignalCfgResourceType,ioLineSignalCfgEnable,
     ioLineSignalCfgDescription,ioLineSignalInputCfgLatch,
     ioLineSignalInputCfgInvertSignal,ioLineSignalInputCfgAlarmTrigger,
     ioLineSignalInputCfgAlarmClear,ioLineSignalInputCfgAlarmEmail,
     ioLineSignalInputCfgAlarmSyslog,ioLineSignalInputCfgAlarmSNMP,
     ioLineSignalOutputCfgFailsafe,
     
     ioLineExtSigCfgStatus,ioLineExtSigCfgEnable,ioLineExtSigCfgConnMethod,
     ioLineExtSigCfgHost,ioLineExtSigCfgPort,ioLineExtSigCfgLinkChannel,
     ioLineExtSigCfgKeepalive,ioLineExtSigCfgMultiHost,ioLineExtSigCfgTunnelName,
     
     ioLineMultihostSigStatus,ioLineMultihostModeSig,
     
     ioLineMultihostOutboundSigStatus,ioLineMultihostOutboundSigHostID,
     ioLineMultihostOutboundSigTcpPort, ioLineMultihostOutboundSigTunnel,
     
     ioLineSSLSigStatus,ioLineSSLSigEnabled,ioLineSSLSiguseServer,
     ioLineSSLSigVersion,ioLineSSLSigType,ioLineSSLSigVerifyPeerCertificate,
     ioLineSSLSigCountry,ioLineSSLSigStateProv,ioLineSSLSigLocality,
     ioLineSSLSigOrganisation,ioLineSSLSigOrganisationUnit,
     ioLineSSLSigCommonName,ioLineSSLSigEmail,
     
     ioLineSSLSigCipherStatus,ioLineSSLSigCipherEncryption,
     ioLineSSLSigCipherKeySizeMin,ioLineSSLSigCipherKeySizeMax,
     ioLineSSLSigCipherKeyExchange,ioLineSSLSigCipherHMAC,ioChannelFunction,
     
     ioAnalogStatusEnabled,ioAnalogStatusDescription,ioAnalogFunction,
     ioAnalogStatusInputState,ioAnalogStatusValue,ioAnalogStatusMinimum,
     ioAnalogStatusMaximum,ioAnalogStatusAlarmLevel,ioDigitalStatusEnabled,
     
     ioDigitalStatusDescription,ioDigitalStatusType,ioDigitalFunction,
     ioDigitalStatusState,ioDigitalStatusLatchedInputState,
     ioDigitalStatusInputAlarm,ioDigitalStatusExtensionState,
     
     ioRelayStatusEnabled,ioRelayStatusDescription,ioRelayFunction,
     ioRelayStatusState,ioRelayStatusExtensionState,
     
     ioLineSignalStatusEnabled,ioLineSignalStatusDescription,
     ioLineSignalStatusType,ioLineSignalFunction,ioLineSignalStatusState,
     ioLineSignalStatusLatchedInputState,ioLineSignalStatusInputAlarm,
     ioLineSignalStatusExtensionState,

     clusteringStatus,clusteringServerName,clusteringSlaveIP,clusteringPort,
     clusteringPortName,clusteringSlavePort,clusteringMasterPort,clusteringSlaveIPTunnel,
     clusteringProtocol,
     
     dynamicDNSStatus,dynamicDNSEnabled,dynamicDNSHostname,dynamicDNSUserName,
     dynamicDNSPassword,dynamicDNSSystemType,dynamicDNSWildcard,
     dynamicDNSConnectionMethod,dynamicDNSSSLVerifyPeerCertificate,
     dynamicDNSSSLCountry,dynamicDNSSSLStateProv,dynamicDNSSSLLocality,
     dynamicDNSSSLOrganisation,dynamicDNSSSLOrganisationUnit,
     dynamicDNSSSLCommonName,dynamicDNSSSLEmail,dynamicDNSStatusString,
     
     dynamicDNSSSLCipherStatus,dynamicDNSSSLCipherEncryption,
     dynamicDNSSSLCipherKeySizeMin,dynamicDNSSSLCipherKeySizeMax,
     dynamicDNSSSLCipherKeyExchange,dynamicDNSSSLCipherHMAC,
     
     pciCardStatus,pciCardType,
     
     wwanCardStatus,wwanCardType,wwanAPN,wwanUserName,wwanPhoneNumer,
     wwanInitString,wwanNetworkRegistration,wwanSignalStrength,
     
     vmodemPhoneStatus,vmodemPhone,vmodemPhoneIP,vmodemPhonePort,
     vmodemPhoneTunnelName, vmodemPhoneHostName,
     
     ipsecStatus,ipsecName,ipsecAuthMethod,ipsecSecret,ipsecLocalDevice,
     ipsecBootaction,ipsecLocalIpAddress,ipsecLocalExternalIpAddress,
     ipsecLocalNextHop,ipsecLocalHostNetwork,ipsecLocalNetmaskBit,
     ipsecRemoteIpAddress,ipsecRemoteExternalIpAddress,ipsecRemoteNextHop,
     ipsecRemoteHostNetwork,ipsecRemoteNetmaskBit,ipsecRemoteValCritCountry,
     ipsecRemoteValCritStateProv,ipsecRemoteValCritLocality,
     ipsecRemoteValCritOrganisation,ipsecRemoteValCritOrganisationUnit,
     ipsecRemoteValCritCommonName,ipsecRemoteValCritEmail,
     
     ipv6serviceStatus,serviceAutoDiscovery1,serviceDHCPv61,
     serviceRouterAdvertisement1,serviceRouterAdvertisementDHCP1,
     serviceRouterAdvertisementOther1,serviceAutoDiscovery2,
     serviceDHCPv62,serviceRouterAdvertisement2,
     serviceRouterAdvertisementDHCP2,serviceRouterAdvertisementOther2,
     serviceDHCPv6IPAddresses,serviceDHCPv6NetworkPrefix,
     serviceAutoDiscovery3, serviceDHCPv63, serviceRouterAdvertisement3,
     serviceRouterAdvertisementDHCP3, serviceRouterAdvertisementOther3,
     
     ipv6AddressEth1Status,ipv6AddressEth1Addr,ipv6AddressEth1PrefixBits,
     ipv6AddressEth1Auto,ipv6AddressEth1SendAdvertise,
     
     ipv6AddressEth2Status,ipv6AddressEth2Addr,ipv6AddressEth2PrefixBits,
     ipv6AddressEth2Auto,ipv6AddressEth2SendAdvertise,
     
     ipv6AddressEth3Status,ipv6AddressEth3Addr,ipv6AddressEth3PrefixBits,
     ipv6AddressEth3Auto,ipv6AddressEth3SendAdvertise,
     
     ipv6TunnelStatus,ipv6TunnelName,ipv6TunnelMode,ipv6TunnelRemoteHost,
     ipv6TunnelGateway,
     
     pciFiberLanType,pciFiberLanStatus,
     
     l2tpStatus,l2tpIpsec,l2tpAuthMethod,l2tpSecret,l2tpIpsecLocalIpAddr,
     l2tpCountry,l2tpStateProv,l2tpLocality,l2tpOrganisation,
     l2tpOrganisationUnit,l2tpCommonName,l2tpEmail,l2tpPPPLocalIpAddr,
     l2tpPPPRemoteStartIpAddr,l2tpPPPRemoteEndIpAddr,l2tpPap,l2tpChap,
     
     vpnexceptionStatus,vpnexceptionIpAddress,vpnexceptionPrefixBits,
     httpTunProxyBasicStatus,httpTunProxyHost,httpTunProxyPort, httpTunProxyUser,
     httpTunProxyPassword, httpTunProxyDomain,

     httpTunProxyAdvStatus, httpTunProxyKeepaliveInterval,httpTunProxyMaxConnectionAge,

     httpTunTunnelCfgStatus,httpTunTunnelCfgValid,
     httpTunTunnelCfgName,httpTunTunnelCfgMode,httpTunTunnelCfgConnectHost,
     httpTunTunnelCfgConnectUseProxy,httpTunTunnelCfgListenRestrictIp,httpTunTunnelCfgHttps,
     httpTunTunnelCfgRestrictAccess,httpTunTunnelCfgSecret,

     httpTunTunnelStatsName,httpTunTunnelStatsMode,httpTunTunnelStatsConnectHost,
     httpTunTunnelStatsConnected,httpTunTunnelStatsHttps,httpTunTunnelStatsAuthFailed,
     
     httpTunConnectionCfgStatus,httpTunConnectionCfgValid,httpTunConnectionCfgTunnelName,
     httpTunConnectionCfgProtocol,httpTunConnectionCfgDestinationHost,httpTunConnectionCfgDestinationPort,
     httpTunConnectionCfgLocalPort,httpTunConnectionCfgLocalIpAlias,httpTunConnectionCfgRestrictAccess,

     httpTunConnectionStatsTunnelName,httpTunConnectionStatsType,httpTunConnectionStatsProtocol,
     httpTunConnectionStatsDestinationIp,httpTunConnectionStatsDestinationPort,httpTunConnectionStatsSourceIp,
     httpTunConnectionStatsLocalPort,
     
     sftpStatus,sftpCompression,sftpAutoLogin,sftpName,sftpPassword,sftpHost,sftpTunnelName,sftpProtocol,
     sftpRSA,sftpDSA,sftpKeyboard,sftpCipherSSH1,sftpFirstSSH2Cipher,sftpSecondSSH2Cipher,sftpThirdSSH2Cipher,
     sftpFourthSSH2Cipher,sftpFifthSSH2Cipher,
     
     sfpStatus, sfpMediaType1, sfpSgmii1, sfpMediaType2, sfpSgmii2,
     sfpStatus, sfpVendorSerialNumber, sfpVendorName, sfpVendorPartNumber, sfpConnectorType, sfpNominalBitRate, 
     sfpLinkReach9125, sfpLinkReach50125, sfpLinkReach625125, sfpReachCopper, sfpFiberWaveLength, 
     sfpDmiCurrentTempState, sfpDmiRealTimeTemp, 
     sfpDmiHighTempWarn, sfpDmiHighTempAlarm, sfpDmiLowTempWarn, sfpDmiLowTempAlarm, 
     sfpDmiCurrentVoltState, sfpDmiRealTimeVolt, 
     sfpDmiHighVoltWarn, sfpDmiHighVoltAlarm, sfpDmiLowVoltWarn, sfpDmiLowVoltAlarm, 
     sfpDmiCurrentTxBiasState, sfpDmiRealTimeTxBias, 
     sfpDmiHighTxBiasWarn, sfpDmiHighTxBiasAlarm, sfpDmiLowTxBiasWarn, sfpDmiLowTxBiasAlarm, 
     sfpDmiCurrentTxPowerState, sfpDmiRealTimeTxPower, 
     sfpDmiHighTxPowerWarn, sfpDmiHighTxPowerAlarm, sfpDmiLowTxPowerWarn,sfpDmiLowTxPowerAlarm, 
     sfpDmiCurrentRxPowerState, sfpDmiRealTimeRxPower,
     sfpDmiHighRxPowerWarn, sfpDmiHighRxPowerAlarm, sfpDmiLowRxPowerWarn, sfpDmiLowRxPowerAlarm,
     
     fpStatus, fpLcdAutoScrollEnable, fpLcdScrollDelay, fpLcdIdleDelay, fpCustomTextLine1,  fpCustomTextLine2,
     fpKeypadLock,fpKeypadPin, fpKeypadPinNumber,
     fpLcdScreenOrder1, fpLcdScreenOrder2, fpLcdScreenOrder3, fpLcdScreenOrder4, fpLcdScreenOrder5, fpLcdScreenOrder6, 
     fpLcdScreenOrder7, fpLcdScreenOrder8, fpLcdScreenOrder9, fpLcdScreenOrder10, fpLcdScreenOrder11        
     
  }
  STATUS       current
  DESCRIPTION 
            "The group of objects for identifying and determining the 
             configuration and current timeliness values of the 
             Perle IOLAN SDS, SCS and STS.
                 "
  ::= { sdsMIBGroups 1 }


sdsMIBNotificationsGroup NOTIFICATION-GROUP
  NOTIFICATIONS {
      sdsMIBIoDigitalInputAlarmSensor,sdsMIBIoDigitalInputAlarmClear,
      
      sdsMIBIoLineInputDSRAlarm,sdsMIBIoLineInputDCDAlarm,sdsMIBIoLineInputCTSAlarm,
      sdsMIBIoLineInputDSRAlarmClear,sdsMIBIoLineInputDCDAlarmClear,sdsMIBIoLineInputCTSAlarmClear,

      sdsMIBIoAnalogInputAlarmSeverityLevel1,sdsMIBIoAnalogInputAlarmSeverityLevel2,
      sdsMIBIoAnalogInputAlarmSeverityLevel3,sdsMIBIoAnalogInputAlarmSeverityLevel4,
      sdsMIBIoAnalogInputAlarmSeverityLevel5,
      sdsMIBIoAnalogInputAlarmSeverityLevel1Clear,sdsMIBIoAnalogInputAlarmSeverityLevel2Clear,
      sdsMIBIoAnalogInputAlarmSeverityLevel3Clear,sdsMIBIoAnalogInputAlarmSeverityLevel4Clear,
      sdsMIBIoAnalogInputAlarmSeverityLevel5Clear,
      
      sdsMIBEthernetLinkDown, sdsMIBEthernetLinkUp 
  }
  STATUS        current
  DESCRIPTION
           "The group of notifications which is implemented for the
            Perle IOLAN SDS, SCS and STS."
          
  ::= { sdsMIBGroups 2 }
   
 END
