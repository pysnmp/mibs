IPV6-UDP-MIB DEFINITIONS ::= BEGIN

 IMPORTS
    MODULE-COMPLIANCE, OBJECT-GROUP      FROM SNMPv2-CONF
    MODULE-IDENTITY, OBJECT-TYPE,
    mib-2, experimental                  FROM SNMPv2-SMI
    Ipv6Address, Ipv6IfIndexOrZero       FROM IPV6-TC;

 ipv6UdpMIB MODULE-IDENTITY
    LAST-UPDATED "201702220000Z"
    ORGANIZATION "IETF IPv6 MIB Working Group"
    CONTACT-INFO
         "               Mike Daniele

                 Postal: Compaq Computer Corporation
                         110 Spitbrook Rd
                         Nashua, NH 03062.
                         US

                 Phone:  +1 603 884 1423
                 Email:  daniele@zk3.dec.com"
    DESCRIPTION
         "The obsolete MIB module for entities implementing UDP
         over IPv6.  Use the UDP-MIB instead.

         Copyright (c) 2017 IETF Trust and the persons
         identified as authors of the code.  All rights reserved.

         Redistribution and use in source and binary forms,
         with or without modification, is permitted pursuant to,
         and subject to the license terms contained in, the
         Simplified BSD License set forth in Section 4.c of the IETF
         Trust's Legal Provisions Relating to IETF Documents
         (http://trustee.ietf.org/license-info)."
    REVISION "201702220000Z"
    DESCRIPTION
         "Obsoleting this MIB module; it has been replaced by
         the revised UDP-MIB (RFC 4113)."
    REVISION "9801290000Z"
    DESCRIPTION
         "First revision, published as RFC 2454"
    ::= { experimental 87 }

 -- objects specific to UDP for IPv6

 udp      OBJECT IDENTIFIER ::= { mib-2 7 }

 -- the UDP over IPv6 Listener table

 -- This table contains information about this entity's
 -- UDP/IPv6 endpoints.  Only endpoints utilizing IPv6 addresses
 -- are contained in this table.  This entity's UDP/IPv4 endpoints
 -- are contained in udpTable.

 ipv6UdpTable OBJECT-TYPE
    SYNTAX      SEQUENCE OF Ipv6UdpEntry
    MAX-ACCESS  not-accessible
    STATUS      obsolete
    DESCRIPTION
         "A table containing UDP listener information for
          UDP/IPv6 endpoints.

          This table is obsoleted by UDP-MIB::udpEndpointTable."
    ::= { udp 6 }

 ipv6UdpEntry OBJECT-TYPE
    SYNTAX      Ipv6UdpEntry
    MAX-ACCESS  not-accessible
    STATUS      obsolete
    DESCRIPTION
         "Information about a particular current UDP listener.

          Note that conceptual rows in this table require an
          additional index object compared to udpTable, since
          IPv6 addresses are not guaranteed to be unique on the
          managed node.

          This entry is obsoleted by UDP-MIB::udpEndpointTable."
    INDEX   { ipv6UdpLocalAddress,
              ipv6UdpLocalPort,
              ipv6UdpIfIndex }
    ::= { ipv6UdpTable 1 }

 Ipv6UdpEntry ::= SEQUENCE {
    ipv6UdpLocalAddress    Ipv6Address,
    ipv6UdpLocalPort       INTEGER,
    ipv6UdpIfIndex         Ipv6IfIndexOrZero }

 ipv6UdpLocalAddress OBJECT-TYPE
    SYNTAX       Ipv6Address
    MAX-ACCESS   not-accessible
    STATUS       obsolete
    DESCRIPTION
         "The local IPv6 address for this UDP listener.
          In the case of a UDP listener which is willing
          to accept datagrams for any IPv6 address
          associated with the managed node, the value ::0
          is used.

          This object is obsoleted by UDP-MIB::udpEndpointLocalAddress."
    ::= { ipv6UdpEntry 1 }

 ipv6UdpLocalPort OBJECT-TYPE
     SYNTAX     INTEGER (0..65535)
     MAX-ACCESS not-accessible
     STATUS     obsolete
     DESCRIPTION
         "The local port number for this UDP listener.

         This object is obsoleted by UDP-MIB::udpEndpointLocalPort."
     ::= { ipv6UdpEntry 2 }

 ipv6UdpIfIndex OBJECT-TYPE
    SYNTAX     Ipv6IfIndexOrZero
    MAX-ACCESS   read-only
    STATUS     obsolete
    DESCRIPTION
         "An index object used to disambiguate conceptual rows in
          the table, since the ipv6UdpLocalAddress/ipv6UdpLocalPort
          pair may not be unique.

          This object identifies the local interface that is
          associated with ipv6UdpLocalAddress for this UDP listener.
          If such a local interface cannot be determined, this object
          should take on the value 0.  (A possible example of this
          would be if the value of ipv6UdpLocalAddress is ::0.)

          The interface identified by a particular non-0 value of
          this index is the same interface as identified by the same
          value of ipv6IfIndex.

          The value of this object must remain constant during
          the life of this UDP endpoint.

          This object is obsoleted by the zone identifier in
          an InetAddressIPv6z address in
          UDP-MIB::udpEndpointLocalAddress."
    ::= { ipv6UdpEntry 3 }

 --
 -- conformance information
 --

 ipv6UdpConformance OBJECT IDENTIFIER ::= { ipv6UdpMIB 2 }

 ipv6UdpCompliances OBJECT IDENTIFIER ::= { ipv6UdpConformance 1 }
 ipv6UdpGroups      OBJECT IDENTIFIER ::= { ipv6UdpConformance 2 }

 -- compliance statements

 ipv6UdpCompliance MODULE-COMPLIANCE
    STATUS  obsolete
    DESCRIPTION
         "The compliance statement for SNMPv2 entities which
          implement UDP over IPv6.

          This object is obsoleted by UDP-MIB::udpMIBCompliance2."
    MODULE  -- this module
    MANDATORY-GROUPS { ipv6UdpGroup }
    ::= { ipv6UdpCompliances 1 }

 ipv6UdpGroup OBJECT-GROUP
    OBJECTS   { -- these are defined in this module
                -- ipv6UdpLocalAddress (not-accessible)
                -- ipv6UdpLocalPort (not-accessible)
                ipv6UdpIfIndex }
    STATUS    obsolete
    DESCRIPTION
         "The group of objects providing management of
          UDP over IPv6.

          This group is obsoleted by several groups in UDP-MIB."
    ::= { ipv6UdpGroups 1 }

 END
