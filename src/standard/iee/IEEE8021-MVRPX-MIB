IEEE8021-MVRPX-MIB
 DEFINITIONS ::= BEGIN

-- ******************************************************************
-- IEEE P802.1Q(TM) Multiple VLAN Registration Protocol Extension MIB
-- ******************************************************************

IMPORTS
    MODULE-IDENTITY,
    OBJECT-TYPE
          FROM SNMPv2-SMI    -- [RFC2578]
    TruthValue
           FROM SNMPv2-TC     -- [RFC2579]
    MODULE-COMPLIANCE,
    OBJECT-GROUP         FROM SNMPv2-CONF   -- [RFC2580]
    systemGroup
          FROM SNMPv2-MIB    -- [RFC3418]
    ieee8021BridgeBasePortEntry

                         FROM IEEE8021-BRIDGE-MIB -- IEEE Std 802.1Q
   ;

ieee8021MvrpxMib
 MODULE-IDENTITY
    LAST-UPDATED "202103050000Z" -- March 5, 2021
    ORGANIZATION "IEEE 802.1 Working Group"
    CONTACT-INFO
        "  WG-URL: http://www.ieee802.org/1/
         WG-EMail: stds-802-1-l@ieee.org
          Contact: IEEE 802.1 Working Group Chair
           Postal: C/O IEEE 802.1 Working Group
                   IEEE Standards Association
                   445 Hoes Lane
                   Piscataway, NJ 08854
                   USA
           E-mail: stds-802-1-chairs@ieee.org"
   DESCRIPTION 
       "Multiple VLAN Registration Protocol extension module for
        managing MVRP extensions defined in IEEE Std 802.1Q

        Unless otherwise indicated, the references in this MIB
        module are to IEEE Std 802.1Q-2022.

        Copyright (C) IEEE (2022).
        This version of this MIB module is part of IEEE Std 802.1Q;
        see that standard for full legal notices."

    REVISION "202103050000Z" -- March 5, 2021
    DESCRIPTION
            "Published as part of IEEE Std 802.1Q-2022.
            Cross references and contact information updated."

    REVISION "201807010000Z" -- July 1, 2018
    DESCRIPTION
            "Published as part of IEEE Std 802.1Q 2018 revision.
            Cross references updated and corrected."
            
    REVISION "201412150000Z" -- December 15, 2014
    DESCRIPTION
            "Published as part of IEEE Std 802.1Q 2014 revision.
            Cross references updated and corrected."

   REVISION       "201104050000Z"    -- (YYYYMMDDHHMM Zulu=GMT)
   DESCRIPTION 
      "Included in IEEE Std 802.1Qbe-2011

        Copyright (C) IEEE (2011)."
    ::= { iso(1) org(3) ieee(111)
         standards-association-numbers-series-standards (2)
         lan-man-stds (802) ieee802dot1 (1) ieee802dot1mibs (1) 22 }

ieee8021MvrpxMIBObjects
   OBJECT IDENTIFIER ::= { ieee8021MvrpxMib 1 }
ieee8021MvrpxConformance
  OBJECT IDENTIFIER ::= { ieee8021MvrpxMib 2 }



-- =============================================================
-- MVRP extension augmentation of the Generic Bridge Port Table
-- =============================================================

ieee8021MvrpxPortTable
 OBJECT-TYPE
    SYNTAX SEQUENCE OF Ieee8021MvrpxPortEntry
    MAX-ACCESS  not-accessible
    STATUS      current
    DESCRIPTION
       "A table that contains controls for the Multiple VLAN
        Registration Protocol (MVRP) state machines for all of the Ports
        of a Bridge."
    REFERENCE   "12.9.2"
    ::= { ieee8021MvrpxMIBObjects 1 }

ieee8021MvrpxPortEntry
 OBJECT-TYPE
    SYNTAX Ieee8021MvrpxPortEntry
    MAX-ACCESS  not-accessible
    STATUS      current
    DESCRIPTION
       "Each entry contains the MVRP Registrar controls for one Port."
AUGMENTS { ieee8021BridgeBasePortEntry }
    ::= { ieee8021MvrpxPortTable 1 }

Ieee8021MvrpxPortEntry
 ::= SEQUENCE {
        ieee8021MvrpxPortNewOnly             TruthValue,
        ieee8021MvrpxPortMvrpNewPropagated   TruthValue,
        ieee8021MvrpxPortXmitZero            TruthValue
    }

ieee8021MvrpxPortNewOnly
 OBJECT-TYPE
    SYNTAX      TruthValue
    MAX-ACCESS  read-create
    STATUS      current
    DESCRIPTION
       "The mode of operation of the MVRP state machines on
        this port, if enabled.  The value of this object and the value
        of the individual Port+Attribute type enable object
        ieee8021QBridgePortMvrpEnabledStatus combine to control the
        state machines as follows:

        ieee8021MvrpxPortNewOnly
                            ieee8021QBridgePortMvrpEnabledStatus
                                            MVRP state machines

        not implemented     true(1)         Full participant
        false(2)            true(1)         Full participant
        true(1)             true(1)         New-only participant
        not implemented     false(2)        MVRP disabled
        false(2)            false(2)        MVRP disabled
        true(1)             false(2)        MVRP disabled

        This object affects all MVRP Applicant and Registrar state
        machines on this port. A change to the value of this object
        will cause a reset of all MVRP state machines for this attribute
        type on this port.

        The value of this object MUST be retained across
        reinitializations of the management system."
    REFERENCE   "12.9.2.1.3, 12.9.2.2.2"
    DEFVAL      { false }
    ::= { ieee8021MvrpxPortEntry 1 }

ieee8021MvrpxPortMvrpNewPropagated
 OBJECT-TYPE
    SYNTAX      TruthValue
    MAX-ACCESS  read-create
    STATUS      current
    DESCRIPTION
       "The mode of operation of the MVRP on this port, if enabled.
        If this object contains the value true(1), then all Static VLAN
        Registration Entries that are Registration Fixed are treated as
        Registration Fixed (New propagated), and if false(2), as
        Registration Fixed (New ignored)

        This object affects only the MVRP Applicant and Registrar state
        machines on this port. A change to the value of this object
        will cause a reset of all MVRP state machines on this port.

        The value of this object MUST be retained across
        reinitializations of the management system."
    REFERENCE   "12.7.7.1.2:d, 12.7.7.3.3:d"
    DEFVAL      { false }
    ::= { ieee8021MvrpxPortEntry 2 }

ieee8021MvrpxPortXmitZero
 OBJECT-TYPE
    SYNTAX      TruthValue
    MAX-ACCESS  read-create
    STATUS      current
    DESCRIPTION
       "Selects whether MVRP is enabled to transmit 0 as the attribute
        value for the one VLAN ID for which this Port is in the untagged
        set, true(1) to enable transmit 0, and false(2) to transmit the
        VLAN ID.  The value 0 is not transmitted unless
        ieee8021MvrpxPortNewOnly is true(1).

        This feature is optional.  If not supported, the system SHALL
        NOT allow this object to be set to the value true(1).

        The value of this object MUST be retained across
        reinitializations of the management system."
    REFERENCE   "12.9.2.1.3:c, 12.9.2.2.2:e, 11.2.3.1.7"
    DEFVAL      { false }
    ::= { ieee8021MvrpxPortEntry 3 }



-- ******************************************************************
-- IEEE 802.1Qbe MVRP extension Module - Conformance Information
-- ******************************************************************

ieee8021MvrpxCompliances
     OBJECT IDENTIFIER
    ::= { ieee8021MvrpxConformance 1 }
ieee8021MvrpxGroups
          OBJECT IDENTIFIER
    ::= { ieee8021MvrpxConformance 2 }



-- ******************************************************************
-- Units of conformance
-- ******************************************************************

ieee8021MvrpxReqdGroup
 OBJECT-GROUP
    OBJECTS {
        ieee8021MvrpxPortNewOnly,
        ieee8021MvrpxPortMvrpNewPropagated,
        ieee8021MvrpxPortXmitZero
    }
    STATUS current
    DESCRIPTION
       "Objects in the MVRP extension augmentation table required
        group."
    ::= { ieee8021MvrpxGroups 1 }



-- ******************************************************************
-- MIB Module Compliance statements
-- ******************************************************************

ieee8021MvrpxCompliance
 MODULE-COMPLIANCE
    STATUS      current
    DESCRIPTION
       "The compliance statement for support by a Bridge of
        the IEEE8021-MVRPX-MIB module."

    MODULE SNMPv2-MIB -- The SNMPv2-MIB, RFC 3418
        MANDATORY-GROUPS {
            systemGroup
        }

    MODULE
        MANDATORY-GROUPS {
            ieee8021MvrpxReqdGroup
        }

    ::= { ieee8021MvrpxCompliances 1 }

END
