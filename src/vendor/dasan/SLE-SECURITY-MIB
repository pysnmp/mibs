--
-- sle-security-mib.mib
-- MIB generated by MG-SOFT Visual MIB Builder Version 6.0  Build 88
-- Thursday, January 21, 2016 at 14:10:56
--

	SLE-SECURITY-MIB DEFINITIONS ::= BEGIN
 
		IMPORTS
			sleMgmt			
				FROM DASAN-SMI			
			InterfaceIndex			
				FROM IF-MIB			
			InetAddressIPv6			
				FROM INET-ADDRESS-MIB			
			SleControlStatusType, SleControlRequestResultType, SlePermissionType			
				FROM SLE-TC-MIB			
			OBJECT-GROUP, NOTIFICATION-GROUP			
				FROM SNMPv2-CONF			
			TimeTicks, IpAddress, Integer32, Unsigned32, Gauge32, 
			Counter32, BITS, OBJECT-TYPE, MODULE-IDENTITY, NOTIFICATION-TYPE			
				FROM SNMPv2-SMI			
			DateAndTime, TimeStamp, MacAddress			
				FROM SNMPv2-TC;
	
	
		sleSecurity MODULE-IDENTITY 
			LAST-UPDATED "200412100929Z"		-- December 10, 2004 at 09:29 GMT
			ORGANIZATION 
				"Organization."
			CONTACT-INFO 
				"Contact-info."
			DESCRIPTION 
				"Description."
			::= { sleMgmt 7 }

		
	
	
--
-- Node definitions
--
	
		sleSecurityBase OBJECT IDENTIFIER ::= { sleSecurity 1 }

		
		sleSecurityBaseInfo OBJECT IDENTIFIER ::= { sleSecurityBase 1 }

		
		sleSecurityRadiusRetransmissions OBJECT-TYPE
			SYNTAX Integer32
			MAX-ACCESS read-only
			STATUS current
			DESCRIPTION
				"Description"
			::= { sleSecurityBaseInfo 1 }

		
		sleSecurityRadiusTimeouts OBJECT-TYPE
			SYNTAX Integer32
			MAX-ACCESS read-only
			STATUS current
			DESCRIPTION
				"Description"
			::= { sleSecurityBaseInfo 2 }

		
		sleSecurityRadiusInterfaceName OBJECT-TYPE
			SYNTAX OCTET STRING (SIZE (0..255))
			MAX-ACCESS read-only
			STATUS current
			DESCRIPTION
				"Description"
			::= { sleSecurityBaseInfo 3 }

		
		sleSecurityRadiusInterfaceAddress OBJECT-TYPE
			SYNTAX IpAddress
			MAX-ACCESS read-only
			STATUS current
			DESCRIPTION
				"Description"
			::= { sleSecurityBaseInfo 4 }

		
		sleSecurityTacacsInterfaceName OBJECT-TYPE
			SYNTAX OCTET STRING (SIZE (0..255))
			MAX-ACCESS read-only
			STATUS current
			DESCRIPTION
				"Description"
			::= { sleSecurityBaseInfo 5 }

		
		sleSecurityTacacsInterfaceAddress OBJECT-TYPE
			SYNTAX IpAddress
			MAX-ACCESS read-only
			STATUS current
			DESCRIPTION
				"Description"
			::= { sleSecurityBaseInfo 6 }

		
		sleSecurityTacacsPort OBJECT-TYPE
			SYNTAX Integer32 (0..65535)
			MAX-ACCESS read-only
			STATUS current
			DESCRIPTION
				"Description"
			::= { sleSecurityBaseInfo 7 }

		
		sleSecurityTacacsAuthType OBJECT-TYPE
			SYNTAX INTEGER
				{
				ascii(0),
				pap(1),
				chap(2)
				}
			MAX-ACCESS read-only
			STATUS current
			DESCRIPTION
				"Description"
			DEFVAL { ascii }
			::= { sleSecurityBaseInfo 8 }

		
		sleSecurityTacacsTimeouts OBJECT-TYPE
			SYNTAX Integer32
			MAX-ACCESS read-only
			STATUS current
			DESCRIPTION
				"Description"
			::= { sleSecurityBaseInfo 9 }

		
		sleSecurityTacacsPriorityLevel OBJECT-TYPE
			SYNTAX INTEGER
				{
				max(0),
				min(1),
				root(2),
				user(3)
				}
			MAX-ACCESS read-only
			STATUS current
			DESCRIPTION
				"Description"
			DEFVAL { min }
			::= { sleSecurityBaseInfo 10 }

		
		sleSecurityDot1xActivity OBJECT-TYPE
			SYNTAX INTEGER
				{
				disable(0),
				enable(1)
				}
			MAX-ACCESS read-only
			STATUS current
			DESCRIPTION
				"Description"
			::= { sleSecurityBaseInfo 11 }

		
		sleSecurityLoginLimits OBJECT-TYPE
			SYNTAX Integer32
			MAX-ACCESS read-only
			STATUS current
			DESCRIPTION
				"The limit number of use login."
			::= { sleSecurityBaseInfo 12 }

		
		sleSecurityLoginLockAttemptsCount OBJECT-TYPE
			SYNTAX Integer32 (3..10)
			MAX-ACCESS read-only
			STATUS current
			DESCRIPTION
				"This feature limits login when login failed for invalid password admin.
				(default attempts: 5, default delay: 5 minutes)"
			::= { sleSecurityBaseInfo 13 }

		
		sleSecurityLoginLockDelayTime OBJECT-TYPE
			SYNTAX Integer32 (1..10)
			MAX-ACCESS read-only
			STATUS current
			DESCRIPTION
				"This feature limits login when login failed for invalid password admin.
				(default attempts: 5, default delay: 5 minutes)"
			::= { sleSecurityBaseInfo 14 }

		
		sleSecurityLoginAccountingMode OBJECT-TYPE
			SYNTAX INTEGER
				{
				none(0),
				start(1),
				stop(2),
				both(3)
				}
			MAX-ACCESS read-only
			STATUS current
			DESCRIPTION
				"The login accounting mode."
			::= { sleSecurityBaseInfo 15 }

		
		sleSecurityBaseControl OBJECT IDENTIFIER ::= { sleSecurityBase 2 }

		
		sleSecurityControlRequest OBJECT-TYPE
			SYNTAX INTEGER
				{
				setSecurityBaseRadiusProfile(1),
				setSecurityBaseTacacsProfile(2),
				setSecurityBaseDot1xActivity(3),
				setSecurityBaseLoginLimits(4),
				setSecurityBaseLoginLockConf(5),
				destroySecurityBaseLoginLockConf(6),
				setLoginAccountingMode(7)
				}
			MAX-ACCESS read-write
			STATUS current
			DESCRIPTION
				"Description"
			::= { sleSecurityBaseControl 1 }

		
		sleSecurityControlStatus OBJECT-TYPE
			SYNTAX SleControlStatusType
			MAX-ACCESS read-only
			STATUS current
			DESCRIPTION
				"Description"
			::= { sleSecurityBaseControl 2 }

		
		sleSecurityControlTimer OBJECT-TYPE
			SYNTAX Gauge32
			MAX-ACCESS read-write
			STATUS current
			DESCRIPTION
				"Description"
			::= { sleSecurityBaseControl 3 }

		
		sleSecurityControlTimeStamp OBJECT-TYPE
			SYNTAX TimeStamp
			MAX-ACCESS read-only
			STATUS current
			DESCRIPTION
				"Description"
			::= { sleSecurityBaseControl 4 }

		
		sleSecurityControlReqResult OBJECT-TYPE
			SYNTAX SleControlRequestResultType
			MAX-ACCESS read-only
			STATUS current
			DESCRIPTION
				"Description"
			::= { sleSecurityBaseControl 5 }

		
		sleSecurityControlRadiusRetransmissions OBJECT-TYPE
			SYNTAX Integer32
			MAX-ACCESS read-write
			STATUS current
			DESCRIPTION
				"Description"
			::= { sleSecurityBaseControl 6 }

		
		sleSecurityControlRadiusTimeouts OBJECT-TYPE
			SYNTAX Integer32
			MAX-ACCESS read-write
			STATUS current
			DESCRIPTION
				"Description"
			::= { sleSecurityBaseControl 7 }

		
		sleSecurityControlRadiusInterfaceName OBJECT-TYPE
			SYNTAX OCTET STRING (SIZE (0..255))
			MAX-ACCESS read-write
			STATUS current
			DESCRIPTION
				"Description"
			::= { sleSecurityBaseControl 8 }

		
		sleSecurityControlRadiusInterfaceAddress OBJECT-TYPE
			SYNTAX IpAddress
			MAX-ACCESS read-write
			STATUS current
			DESCRIPTION
				"Description"
			::= { sleSecurityBaseControl 9 }

		
		sleSecurityControlTacacsInterfaceName OBJECT-TYPE
			SYNTAX OCTET STRING (SIZE (0..255))
			MAX-ACCESS read-write
			STATUS current
			DESCRIPTION
				"Description"
			::= { sleSecurityBaseControl 10 }

		
		sleSecurityControlTacacsInterfaceAddress OBJECT-TYPE
			SYNTAX IpAddress
			MAX-ACCESS read-write
			STATUS current
			DESCRIPTION
				"Description"
			::= { sleSecurityBaseControl 11 }

		
		sleSecurityControlTacacsPort OBJECT-TYPE
			SYNTAX Integer32 (0..65535)
			MAX-ACCESS read-write
			STATUS current
			DESCRIPTION
				"Description"
			::= { sleSecurityBaseControl 12 }

		
		sleSecurityControlTacacsAuthType OBJECT-TYPE
			SYNTAX INTEGER
				{
				ascii(0),
				pap(1),
				chap(2)
				}
			MAX-ACCESS read-write
			STATUS current
			DESCRIPTION
				"Description"
			DEFVAL { ascii }
			::= { sleSecurityBaseControl 13 }

		
		sleSecurityControlTacacsTimeouts OBJECT-TYPE
			SYNTAX Integer32
			MAX-ACCESS read-write
			STATUS current
			DESCRIPTION
				"Description"
			::= { sleSecurityBaseControl 14 }

		
		sleSecurityControlTacacsPriorityLevel OBJECT-TYPE
			SYNTAX INTEGER
				{
				max(0),
				min(1),
				root(2),
				user(3)
				}
			MAX-ACCESS read-write
			STATUS current
			DESCRIPTION
				"Description"
			DEFVAL { min }
			::= { sleSecurityBaseControl 15 }

		
		sleSecurityControlDot1xActivity OBJECT-TYPE
			SYNTAX INTEGER
				{
				disable(0),
				enable(1)
				}
			MAX-ACCESS read-write
			STATUS current
			DESCRIPTION
				"Description"
			::= { sleSecurityBaseControl 16 }

		
		sleSecurityControlLoginLimits OBJECT-TYPE
			SYNTAX Integer32
			MAX-ACCESS read-write
			STATUS current
			DESCRIPTION
				"The limit number of use login."
			::= { sleSecurityBaseControl 17 }

		
		sleSecurityControlLoginLockAttemptsCount OBJECT-TYPE
			SYNTAX Integer32 (3..10)
			MAX-ACCESS read-write
			STATUS current
			DESCRIPTION
				"This feature limits login when login failed for invalid password admin.
				(default attempts: 5, default delay: 5 minutes)"
			::= { sleSecurityBaseControl 18 }

		
		sleSecurityControlLoginLockDelayTime OBJECT-TYPE
			SYNTAX Integer32 (1..10)
			MAX-ACCESS read-write
			STATUS current
			DESCRIPTION
				"This feature limits login when login failed for invalid password admin.
				(default attempts: 5, default delay: 5 minutes)"
			::= { sleSecurityBaseControl 19 }

		
		sleSecurityControlLoginAccountingMode OBJECT-TYPE
			SYNTAX INTEGER
				{
				none(0),
				start(1),
				stop(2),
				both(3)
				}
			MAX-ACCESS read-only
			STATUS current
			DESCRIPTION
				"The login accounting mode."
			::= { sleSecurityBaseControl 20 }

		
		sleSecurityBaseNotification OBJECT IDENTIFIER ::= { sleSecurityBase 3 }

		
		sleSecurityRadiusProfileChanged NOTIFICATION-TYPE
			OBJECTS { sleSecurityRadiusRetransmissions, sleSecurityRadiusTimeouts, sleSecurityRadiusInterfaceName, sleSecurityRadiusInterfaceAddress, sleSecurityControlRequest, 
				sleSecurityControlTimeStamp, sleSecurityControlReqResult }
			STATUS current
			DESCRIPTION 
				"Description"
			::= { sleSecurityBaseNotification 1 }

		
		sleSecurityTacacsProfileChanged NOTIFICATION-TYPE
			OBJECTS { sleSecurityTacacsInterfaceName, sleSecurityTacacsInterfaceAddress, sleSecurityTacacsPort, sleSecurityTacacsAuthType, sleSecurityTacacsTimeouts, 
				sleSecurityTacacsPriorityLevel, sleSecurityControlStatus, sleSecurityControlTimeStamp, sleSecurityControlReqResult }
			STATUS current
			DESCRIPTION 
				"Description"
			::= { sleSecurityBaseNotification 2 }

		
		sleSecurityDot1xActivityChanged NOTIFICATION-TYPE
			OBJECTS { sleSecurityDot1xActivity, sleSecurityControlRequest, sleSecurityControlTimeStamp, sleSecurityControlReqResult }
			STATUS current
			DESCRIPTION 
				"Description"
			::= { sleSecurityBaseNotification 3 }

		
		sleSecurityBaseLoginLimitsChanged NOTIFICATION-TYPE
			OBJECTS { sleSecurityControlRequest, sleSecurityControlTimeStamp, sleSecurityControlReqResult, sleSecurityControlLoginLimits }
			STATUS current
			DESCRIPTION 
				"Description."
			::= { sleSecurityBaseNotification 4 }

		
		sleSecurityBaseLoginLockConfChanged NOTIFICATION-TYPE
			OBJECTS { sleSecurityControlRequest, sleSecurityControlTimeStamp, sleSecurityControlReqResult, sleSecurityControlLoginLockAttemptsCount, sleSecurityControlLoginLockDelayTime
				 }
			STATUS current
			DESCRIPTION 
				"setSecurityBaseLoginLockConf "
			::= { sleSecurityBaseNotification 5 }

		
		sleSecurityBaseLoginLockConfDestroyed NOTIFICATION-TYPE
			OBJECTS { sleSecurityControlRequest, sleSecurityControlTimeStamp, sleSecurityControlReqResult }
			STATUS current
			DESCRIPTION 
				"destroySecurityBaseLoginLockConf"
			::= { sleSecurityBaseNotification 6 }

		
		sleSecurityLoginAccountingModeChanged NOTIFICATION-TYPE
			OBJECTS { sleSecurityControlRequest, sleSecurityControlTimeStamp, sleSecurityControlReqResult, sleSecurityControlLoginAccountingMode }
			STATUS current
			DESCRIPTION 
				"setLoginAccountingMode"
			::= { sleSecurityBaseNotification 7 }

		
		sleAAA OBJECT IDENTIFIER ::= { sleSecurity 2 }

		
		sleAaaTable OBJECT-TYPE
			SYNTAX SEQUENCE OF SleAaaEntry
			MAX-ACCESS not-accessible
			STATUS current
			DESCRIPTION
				"Description."
			::= { sleAAA 1 }

		
		sleAaaEntry OBJECT-TYPE
			SYNTAX SleAaaEntry
			MAX-ACCESS not-accessible
			STATUS current
			DESCRIPTION
				"Description."
			INDEX { sleAaaSession, sleAaaAuthen }
			::= { sleAaaTable 1 }

		
		SleAaaEntry ::=
			SEQUENCE { 
				sleAaaSession
					INTEGER,
				sleAaaAuthen
					INTEGER,
				sleAaaEnable
					INTEGER,
				sleAaaPrimarySequence
					INTEGER
			 }

		sleAaaSession OBJECT-TYPE
			SYNTAX INTEGER
				{
				console(1),
				remote(2)
				}
			MAX-ACCESS read-only
			STATUS current
			DESCRIPTION
				"Location of authentication."
			::= { sleAaaEntry 1 }

		
		sleAaaAuthen OBJECT-TYPE
			SYNTAX INTEGER
				{
				host(1),
				radius(2),
				tacacs(3)
				}
			MAX-ACCESS read-only
			STATUS current
			DESCRIPTION
				"The kind of authentication."
			::= { sleAaaEntry 2 }

		
		sleAaaEnable OBJECT-TYPE
			SYNTAX INTEGER
				{
				disable(0),
				enable(1)
				}
			MAX-ACCESS read-only
			STATUS current
			DESCRIPTION
				"Enable or disable the corresponding authen method."
			::= { sleAaaEntry 3 }

		
		sleAaaPrimarySequence OBJECT-TYPE
			SYNTAX INTEGER (1..3)
			MAX-ACCESS read-only
			STATUS current
			DESCRIPTION
				"The primary priority of the corresponding authen method"
			::= { sleAaaEntry 4 }

		
		sleAaaControl OBJECT IDENTIFIER ::= { sleAAA 2 }

		
		sleAaaControlRequest OBJECT-TYPE
			SYNTAX INTEGER { setAaaProfile(1) }
			MAX-ACCESS read-write
			STATUS current
			DESCRIPTION
				"Description"
			::= { sleAaaControl 1 }

		
		sleAaaControlStatus OBJECT-TYPE
			SYNTAX SleControlStatusType
			MAX-ACCESS read-only
			STATUS current
			DESCRIPTION
				"Describes the status of a user command group, 
				used for block commands while a command execution in process."
			::= { sleAaaControl 2 }

		
		sleAaaControlTimer OBJECT-TYPE
			SYNTAX Gauge32
			MAX-ACCESS read-write
			STATUS current
			DESCRIPTION
				"Maximum command duration time in case of long running."
			::= { sleAaaControl 3 }

		
		sleAaaControlTimeStamp OBJECT-TYPE
			SYNTAX TimeStamp
			MAX-ACCESS read-only
			STATUS current
			DESCRIPTION
				"Time stamp attribute set at end of command."
			::= { sleAaaControl 4 }

		
		sleAaaControlReqResult OBJECT-TYPE
			SYNTAX SleControlRequestResultType
			MAX-ACCESS read-only
			STATUS current
			DESCRIPTION
				"Command result attribute."
			::= { sleAaaControl 5 }

		
		sleAaaControlSession OBJECT-TYPE
			SYNTAX INTEGER
				{
				console(1),
				remote(2)
				}
			MAX-ACCESS read-write
			STATUS current
			DESCRIPTION
				"Location of authentication."
			::= { sleAaaControl 6 }

		
		sleAaaControlAuthen OBJECT-TYPE
			SYNTAX INTEGER
				{
				host(1),
				radius(2),
				tacacs(3)
				}
			MAX-ACCESS read-write
			STATUS current
			DESCRIPTION
				"The kind of authentication."
			::= { sleAaaControl 7 }

		
		sleAaaControlEnable OBJECT-TYPE
			SYNTAX INTEGER
				{
				disable(0),
				enable(1)
				}
			MAX-ACCESS read-write
			STATUS current
			DESCRIPTION
				"Enable or disable the corresponding authen method."
			::= { sleAaaControl 8 }

		
		sleAaaControlPrimaryFlag OBJECT-TYPE
			SYNTAX INTEGER
				{
				disable(0),
				enable(1)
				}
			MAX-ACCESS read-write
			STATUS current
			DESCRIPTION
				"The primary validation flag of the corresponding authen method"
			::= { sleAaaControl 9 }

		
		sleAaaNotification OBJECT IDENTIFIER ::= { sleAAA 3 }

		
		sleAaaProfileChanged NOTIFICATION-TYPE
			OBJECTS { sleAaaControlRequest, sleAaaControlTimeStamp, sleAaaControlReqResult, sleAaaEnable, sleAaaPrimarySequence
				 }
			STATUS current
			DESCRIPTION 
				"Description
				"
			::= { sleAaaNotification 1 }

		
		sleRadiusServer OBJECT IDENTIFIER ::= { sleSecurity 3 }

		
		sleRadiusServerTable OBJECT-TYPE
			SYNTAX SEQUENCE OF SleRadiusServerEntry
			MAX-ACCESS not-accessible
			STATUS current
			DESCRIPTION
				"Description."
			::= { sleRadiusServer 1 }

		
		sleRadiusServerEntry OBJECT-TYPE
			SYNTAX SleRadiusServerEntry
			MAX-ACCESS not-accessible
			STATUS current
			DESCRIPTION
				"Description."
			INDEX { sleRadiusServerAddress }
			::= { sleRadiusServerTable 1 }

		
		SleRadiusServerEntry ::=
			SEQUENCE { 
				sleRadiusServerAddress
					IpAddress,
				sleRadiusServerClientKey
					OCTET STRING,
				sleRadiusServerAuthPort
					INTEGER,
				sleRadiusServerAccPort
					INTEGER,
				sleRadiusServerMode
					BITS
			 }

		sleRadiusServerAddress OBJECT-TYPE
			SYNTAX IpAddress
			MAX-ACCESS read-only
			STATUS current
			DESCRIPTION
				"The IP address of the RADIUS server referred 
				to in this table entry."
			::= { sleRadiusServerEntry 1 }

		
		sleRadiusServerClientKey OBJECT-TYPE
			SYNTAX OCTET STRING (SIZE (0..255))
			MAX-ACCESS read-only
			STATUS current
			DESCRIPTION
				"The key to be used in communication between the 
				device and the Radius server."
			::= { sleRadiusServerEntry 2 }

		
		sleRadiusServerAuthPort OBJECT-TYPE
			SYNTAX INTEGER (0..65535)
			MAX-ACCESS read-only
			STATUS current
			DESCRIPTION
				"The UDP port the client is using to send requests to this server for authentication."
			::= { sleRadiusServerEntry 3 }

		
		sleRadiusServerAccPort OBJECT-TYPE
			SYNTAX INTEGER (0..65535)
			MAX-ACCESS read-only
			STATUS current
			DESCRIPTION
				"The UDP port the client is using to send requests to this server for accounting."
			::= { sleRadiusServerEntry 4 }

		
		sleRadiusServerMode OBJECT-TYPE
			SYNTAX BITS
				{
				aaa(0),
				dot1x(1)
				}
			MAX-ACCESS read-only
			STATUS current
			DESCRIPTION
				"Radius Server operation mode: if set bit 0, is used 
				in login, and if set bit 1, is used in 802.1X (dot1x)."
			::= { sleRadiusServerEntry 5 }

		
		sleRadiusServerControl OBJECT IDENTIFIER ::= { sleRadiusServer 2 }

		
		sleRadiusServerControlRequest OBJECT-TYPE
			SYNTAX INTEGER
				{
				createRadiusServer(1),
				destroyRadiusServer(2),
				setRadiusServerProfile(3)
				}
			MAX-ACCESS read-write
			STATUS current
			DESCRIPTION
				"The MIB object for the user command."
			::= { sleRadiusServerControl 1 }

		
		sleRadiusServerControlStatus OBJECT-TYPE
			SYNTAX SleControlStatusType
			MAX-ACCESS read-only
			STATUS current
			DESCRIPTION
				"Describes the status of a user command group, 
				used for block commands while a command execution in process."
			::= { sleRadiusServerControl 2 }

		
		sleRadiusServerControlTimer OBJECT-TYPE
			SYNTAX Gauge32
			MAX-ACCESS read-write
			STATUS current
			DESCRIPTION
				"Maximum command duration time in case of long running"
			::= { sleRadiusServerControl 3 }

		
		sleRadiusServerControlTimeStamp OBJECT-TYPE
			SYNTAX TimeStamp
			MAX-ACCESS read-only
			STATUS current
			DESCRIPTION
				"Time stamp attribute set at end of command."
			::= { sleRadiusServerControl 4 }

		
		sleRadiusServerControlReqResult OBJECT-TYPE
			SYNTAX SleControlRequestResultType
			MAX-ACCESS read-only
			STATUS current
			DESCRIPTION
				"Command result attribute."
			::= { sleRadiusServerControl 5 }

		
		sleRadiusServerControlAddress OBJECT-TYPE
			SYNTAX IpAddress
			MAX-ACCESS read-write
			STATUS current
			DESCRIPTION
				"The IP address of the RADIUS server referred to 
				in this table entry."
			::= { sleRadiusServerControl 6 }

		
		sleRadiusServerControlClientKey OBJECT-TYPE
			SYNTAX OCTET STRING (SIZE (0..255))
			MAX-ACCESS read-write
			STATUS current
			DESCRIPTION
				"The key to be used in communication between 
				the device and the Radius server."
			::= { sleRadiusServerControl 7 }

		
		sleRadiusServerControlAuthPort OBJECT-TYPE
			SYNTAX Integer32 (0..65535)
			MAX-ACCESS read-write
			STATUS current
			DESCRIPTION
				"The service port  number for communication with server."
			::= { sleRadiusServerControl 8 }

		
		sleRadiusServerControlAccPort OBJECT-TYPE
			SYNTAX Integer32 (0..65535)
			MAX-ACCESS read-write
			STATUS current
			DESCRIPTION
				"The service port  number for communication with server."
			::= { sleRadiusServerControl 9 }

		
		sleRadiusServerControlMode OBJECT-TYPE
			SYNTAX BITS
				{
				aaa(0),
				dot1x(1)
				}
			MAX-ACCESS read-write
			STATUS current
			DESCRIPTION
				"Description."
			::= { sleRadiusServerControl 10 }

		
		sleRadiusServerNotification OBJECT IDENTIFIER ::= { sleRadiusServer 3 }

		
		sleRadiusServerCreated NOTIFICATION-TYPE
			OBJECTS { sleRadiusServerControlRequest, sleRadiusServerControlTimeStamp, sleRadiusServerControlReqResult, sleRadiusServerClientKey, sleRadiusServerAccPort, 
				sleRadiusServerAuthPort, sleRadiusServerMode }
			STATUS current
			DESCRIPTION 
				"Description"
			::= { sleRadiusServerNotification 1 }

		
		sleRadiusServerDestroyed NOTIFICATION-TYPE
			OBJECTS { sleRadiusServerControlRequest, sleRadiusServerControlTimeStamp, sleRadiusServerControlReqResult, sleRadiusServerControlAddress }
			STATUS current
			DESCRIPTION 
				"Description"
			::= { sleRadiusServerNotification 2 }

		
		sleRadiusServerProfileChanged NOTIFICATION-TYPE
			OBJECTS { sleRadiusServerControlRequest, sleRadiusServerControlTimeStamp, sleRadiusServerControlReqResult, sleRadiusServerClientKey, sleRadiusServerAuthPort, 
				sleRadiusServerAccPort, sleRadiusServerMode }
			STATUS current
			DESCRIPTION 
				"Description"
			::= { sleRadiusServerNotification 3 }

		
		sleTacacsServer OBJECT IDENTIFIER ::= { sleSecurity 4 }

		
		sleTacacsServerTable OBJECT-TYPE
			SYNTAX SEQUENCE OF SleTacacsServerEntry
			MAX-ACCESS not-accessible
			STATUS current
			DESCRIPTION
				"Description."
			::= { sleTacacsServer 1 }

		
		sleTacacsServerEntry OBJECT-TYPE
			SYNTAX SleTacacsServerEntry
			MAX-ACCESS not-accessible
			STATUS current
			DESCRIPTION
				"Description."
			INDEX { sleTacacsServerAddress }
			::= { sleTacacsServerTable 1 }

		
		SleTacacsServerEntry ::=
			SEQUENCE { 
				sleTacacsServerAddress
					IpAddress,
				sleTacacsServerClientKey
					OCTET STRING
			 }

		sleTacacsServerAddress OBJECT-TYPE
			SYNTAX IpAddress
			MAX-ACCESS read-only
			STATUS current
			DESCRIPTION
				"The IP address of the TACACS accounting server 
				referred to in this table entry."
			::= { sleTacacsServerEntry 1 }

		
		sleTacacsServerClientKey OBJECT-TYPE
			SYNTAX OCTET STRING (SIZE (0..255))
			MAX-ACCESS read-only
			STATUS current
			DESCRIPTION
				"The key to be used in communication between the 
				device and the Tacacs server."
			::= { sleTacacsServerEntry 2 }

		
		sleTacacsServerControl OBJECT IDENTIFIER ::= { sleTacacsServer 2 }

		
		sleTacacsServerControlRequest OBJECT-TYPE
			SYNTAX INTEGER
				{
				createTacacsServer(1),
				destroyTacacsServer(2),
				setTacacsServerClientKey(3)
				}
			MAX-ACCESS read-write
			STATUS current
			DESCRIPTION
				"The MIB object for the user command."
			::= { sleTacacsServerControl 1 }

		
		sleTacacsServerControlStatus OBJECT-TYPE
			SYNTAX SleControlStatusType
			MAX-ACCESS read-only
			STATUS current
			DESCRIPTION
				"Describes the status of a user command group, used 
				for block commands while a command execution in process."
			::= { sleTacacsServerControl 2 }

		
		sleTacacsServerControlTimer OBJECT-TYPE
			SYNTAX Gauge32
			MAX-ACCESS read-write
			STATUS current
			DESCRIPTION
				"Maximum command duration time in case of long running."
			::= { sleTacacsServerControl 3 }

		
		sleTacacsServerControlTimeStamp OBJECT-TYPE
			SYNTAX TimeStamp
			MAX-ACCESS read-only
			STATUS current
			DESCRIPTION
				"Time stamp attribute set at end of command."
			::= { sleTacacsServerControl 4 }

		
		sleTacacsServerControlReqResult OBJECT-TYPE
			SYNTAX SleControlRequestResultType
			MAX-ACCESS read-only
			STATUS current
			DESCRIPTION
				"Command result attribute."
			::= { sleTacacsServerControl 5 }

		
		sleTacacsServerControlAddress OBJECT-TYPE
			SYNTAX IpAddress
			MAX-ACCESS read-write
			STATUS current
			DESCRIPTION
				"The IP address of the TACACS accounting server 
				referred to in this table entry."
			::= { sleTacacsServerControl 6 }

		
		sleTacacsServerControlClientKey OBJECT-TYPE
			SYNTAX OCTET STRING (SIZE (0..255))
			MAX-ACCESS read-write
			STATUS current
			DESCRIPTION
				"The key to be used in communication between the 
				device and the Tacacs server."
			::= { sleTacacsServerControl 7 }

		
		sleTacacsServerNotification OBJECT IDENTIFIER ::= { sleTacacsServer 3 }

		
		sleTacacsServerCreated NOTIFICATION-TYPE
			OBJECTS { sleTacacsServerControlRequest, sleTacacsServerControlTimeStamp, sleTacacsServerControlReqResult, sleTacacsServerClientKey }
			STATUS current
			DESCRIPTION 
				"Description"
			::= { sleTacacsServerNotification 1 }

		
		sleTacacsServerDestroyed NOTIFICATION-TYPE
			OBJECTS { sleTacacsServerControlRequest, sleTacacsServerControlTimeStamp, sleTacacsServerControlReqResult, sleTacacsServerControlAddress }
			STATUS current
			DESCRIPTION 
				"DescriptionDescription"
			::= { sleTacacsServerNotification 2 }

		
		sleTacacsServerClientKeyChanged NOTIFICATION-TYPE
			OBJECTS { sleTacacsServerControlRequest, sleTacacsServerControlTimeStamp, sleTacacsServerControlReqResult, sleTacacsServerClientKey }
			STATUS current
			DESCRIPTION 
				"Description"
			::= { sleTacacsServerNotification 3 }

		
		sleAcl OBJECT IDENTIFIER ::= { sleSecurity 5 }

		
		sleAclTable OBJECT-TYPE
			SYNTAX SEQUENCE OF SleAclEntry
			MAX-ACCESS not-accessible
			STATUS current
			DESCRIPTION
				"Description"
			::= { sleAcl 1 }

		
		sleAclEntry OBJECT-TYPE
			SYNTAX SleAclEntry
			MAX-ACCESS not-accessible
			STATUS current
			DESCRIPTION
				"Description."
			INDEX { sleAclName }
			::= { sleAclTable 1 }

		
		SleAclEntry ::=
			SEQUENCE { 
				sleAclName
					OCTET STRING,
				sleAclSrcIpAddr
					IpAddress,
				sleAclSrcPrefixLength
					Integer32,
				sleAclDstIpAddr
					IpAddress,
				sleAclDstPrefixLength
					Integer32,
				sleAclDscp
					Integer32,
				sleAclProtocolType
					Integer32,
				sleAclTcpFlag
					BITS,
				sleAclSrcL4Port
					Integer32,
				sleAclDstL4Port
					Integer32,
				sleAclPktLen
					Integer32,
				sleAclValidFlags
					BITS,
				sleAclMatchFlags
					BITS,
				sleAclMatchAction
					INTEGER,
				sleAclNomatchAction
					INTEGER,
				sleAclPriority
					INTEGER
			 }

		sleAclName OBJECT-TYPE
			SYNTAX OCTET STRING (SIZE (0..63))
			MAX-ACCESS read-only
			STATUS current
			DESCRIPTION
				"Description"
			::= { sleAclEntry 1 }

		
		sleAclSrcIpAddr OBJECT-TYPE
			SYNTAX IpAddress
			MAX-ACCESS read-only
			STATUS current
			DESCRIPTION
				"Description"
			::= { sleAclEntry 2 }

		
		sleAclSrcPrefixLength OBJECT-TYPE
			SYNTAX Integer32 (0..31)
			MAX-ACCESS read-only
			STATUS current
			DESCRIPTION
				"Description"
			::= { sleAclEntry 3 }

		
		sleAclDstIpAddr OBJECT-TYPE
			SYNTAX IpAddress
			MAX-ACCESS read-only
			STATUS current
			DESCRIPTION
				"Description"
			::= { sleAclEntry 4 }

		
		sleAclDstPrefixLength OBJECT-TYPE
			SYNTAX Integer32 (0..31)
			MAX-ACCESS read-only
			STATUS current
			DESCRIPTION
				"Description"
			::= { sleAclEntry 5 }

		
		sleAclDscp OBJECT-TYPE
			SYNTAX Integer32
			MAX-ACCESS read-only
			STATUS current
			DESCRIPTION
				"Description"
			DEFVAL { -1 }
			::= { sleAclEntry 6 }

		
		sleAclProtocolType OBJECT-TYPE
			SYNTAX Integer32 (1..255)
			MAX-ACCESS read-only
			STATUS current
			DESCRIPTION
				"Description"
			::= { sleAclEntry 7 }

		
		sleAclTcpFlag OBJECT-TYPE
			SYNTAX BITS
				{
				reserv(0),
				reserv1(1),
				urg(2),
				ack(3),
				psh(4),
				rst(5),
				syn(6),
				fin(7)
				}
			MAX-ACCESS read-only
			STATUS current
			DESCRIPTION
				"Description"
			::= { sleAclEntry 8 }

		
		sleAclSrcL4Port OBJECT-TYPE
			SYNTAX Integer32 (1..65535)
			MAX-ACCESS read-only
			STATUS current
			DESCRIPTION
				"Description"
			::= { sleAclEntry 9 }

		
		sleAclDstL4Port OBJECT-TYPE
			SYNTAX Integer32 (1..65535)
			MAX-ACCESS read-only
			STATUS current
			DESCRIPTION
				"Description"
			::= { sleAclEntry 10 }

		
		sleAclPktLen OBJECT-TYPE
			SYNTAX Integer32 (21..65535)
			MAX-ACCESS read-only
			STATUS current
			DESCRIPTION
				"Description"
			::= { sleAclEntry 11 }

		
		sleAclValidFlags OBJECT-TYPE
			SYNTAX BITS
				{
				aclSrcIpAddress(0),
				aclSrcPrefixLegth(1),
				aclDstIpAddress(2),
				aclDstPrefixLegth(3),
				aclDscp(4),
				aclProtocolType(5),
				aclTcpFlags(6),
				aclSrcL4Port(7),
				aclDstL4Port(8),
				aclPacketLength(9)
				}
			MAX-ACCESS read-only
			STATUS current
			DESCRIPTION
				"Description"
			::= { sleAclEntry 12 }

		
		sleAclMatchFlags OBJECT-TYPE
			SYNTAX BITS
				{
				aclSrcIpAddress(0),
				aclSrcPrefixLegth(1),
				aclDstIpAddress(2),
				aclDstPrefixLength(3),
				aclDscp(4),
				aclProtocolType(5),
				aclTcpFlag(6),
				aclSrcL4Port(7),
				aclDstL4Port(8),
				aclPacketLength(9)
				}
			MAX-ACCESS read-only
			STATUS current
			DESCRIPTION
				"Description"
			::= { sleAclEntry 13 }

		
		sleAclMatchAction OBJECT-TYPE
			SYNTAX INTEGER
				{
				permit(1),
				deny(2)
				}
			MAX-ACCESS read-only
			STATUS current
			DESCRIPTION
				"Description"
			::= { sleAclEntry 14 }

		
		sleAclNomatchAction OBJECT-TYPE
			SYNTAX INTEGER
				{
				permit(1),
				deny(2)
				}
			MAX-ACCESS read-only
			STATUS current
			DESCRIPTION
				"DescriptionDescription"
			::= { sleAclEntry 15 }

		
		sleAclPriority OBJECT-TYPE
			SYNTAX INTEGER
				{
				low(1),
				medium(2),
				high(3),
				highest(4)
				}
			MAX-ACCESS read-only
			STATUS current
			DESCRIPTION
				"Description"
			::= { sleAclEntry 16 }

		
		sleAclControl OBJECT IDENTIFIER ::= { sleAcl 2 }

		
		sleAclControlReqest OBJECT-TYPE
			SYNTAX INTEGER
				{
				createAclRule(1),
				destroyAclRule(2),
				setAclClassifierProfile(3),
				setAclMatchAction(10),
				setAclNomatchAction(11)
				}
			MAX-ACCESS read-write
			STATUS current
			DESCRIPTION
				"DescriptionDescription"
			::= { sleAclControl 1 }

		
		sleAclControlStatus OBJECT-TYPE
			SYNTAX SleControlStatusType
			MAX-ACCESS read-only
			STATUS current
			DESCRIPTION
				"Description"
			::= { sleAclControl 2 }

		
		sleAclControlTimer OBJECT-TYPE
			SYNTAX Gauge32
			MAX-ACCESS read-write
			STATUS current
			DESCRIPTION
				"Description"
			::= { sleAclControl 3 }

		
		sleAclControlTimeStamp OBJECT-TYPE
			SYNTAX TimeStamp
			MAX-ACCESS read-only
			STATUS current
			DESCRIPTION
				"Description"
			::= { sleAclControl 4 }

		
		sleAclControlReqResult OBJECT-TYPE
			SYNTAX SleControlRequestResultType
			MAX-ACCESS read-only
			STATUS current
			DESCRIPTION
				"Description"
			::= { sleAclControl 5 }

		
		sleAclControlName OBJECT-TYPE
			SYNTAX OCTET STRING (SIZE (0..63))
			MAX-ACCESS read-write
			STATUS current
			DESCRIPTION
				"Description"
			::= { sleAclControl 6 }

		
		sleAclControlSrcIpAddr OBJECT-TYPE
			SYNTAX IpAddress
			MAX-ACCESS read-write
			STATUS current
			DESCRIPTION
				"Description"
			::= { sleAclControl 7 }

		
		sleAclControlSrcPrefixLength OBJECT-TYPE
			SYNTAX Integer32 (0..31)
			MAX-ACCESS read-write
			STATUS current
			DESCRIPTION
				"Description"
			::= { sleAclControl 8 }

		
		sleAclControlDstIpAddr OBJECT-TYPE
			SYNTAX IpAddress
			MAX-ACCESS read-write
			STATUS current
			DESCRIPTION
				"DescriptionDescription"
			::= { sleAclControl 9 }

		
		sleAclControlDstPrefixLength OBJECT-TYPE
			SYNTAX Integer32 (0..31)
			MAX-ACCESS read-write
			STATUS current
			DESCRIPTION
				"Description"
			::= { sleAclControl 10 }

		
		sleAclControlDscp OBJECT-TYPE
			SYNTAX Integer32
			MAX-ACCESS read-write
			STATUS current
			DESCRIPTION
				"Description"
			DEFVAL { -1 }
			::= { sleAclControl 11 }

		
		sleAclControlProtocolType OBJECT-TYPE
			SYNTAX Integer32 (1..255)
			MAX-ACCESS read-write
			STATUS current
			DESCRIPTION
				"Description"
			::= { sleAclControl 12 }

		
		sleAclControlTcpFlag OBJECT-TYPE
			SYNTAX BITS
				{
				reserv(0),
				reserv1(1),
				urg(2),
				ack(3),
				psh(4),
				rst(5),
				syn(6),
				fin(7)
				}
			MAX-ACCESS read-write
			STATUS current
			DESCRIPTION
				"Description"
			::= { sleAclControl 13 }

		
		sleAclControlSrcL4Port OBJECT-TYPE
			SYNTAX Integer32 (0..65535)
			MAX-ACCESS read-write
			STATUS current
			DESCRIPTION
				"Description"
			::= { sleAclControl 14 }

		
		sleAclControlDstL4Port OBJECT-TYPE
			SYNTAX Integer32 (0..65535)
			MAX-ACCESS read-write
			STATUS current
			DESCRIPTION
				"Description"
			::= { sleAclControl 15 }

		
		sleAclControlPktLen OBJECT-TYPE
			SYNTAX Integer32 (21..65535)
			MAX-ACCESS read-write
			STATUS current
			DESCRIPTION
				"Description"
			::= { sleAclControl 16 }

		
		sleAclControlValidFlags OBJECT-TYPE
			SYNTAX BITS
				{
				aclSrcIpAddress(0),
				aclSrcPrefixLength(1),
				aclDstIpAddress(2),
				aclDstPrefixLength(3),
				aclDscp(4),
				aclProtocolType(5),
				aclTcpFlag(6),
				aclSrcL4Port(7),
				aclDstL4Port(8),
				aclPacketLength(9)
				}
			MAX-ACCESS read-write
			STATUS current
			DESCRIPTION
				"Description"
			::= { sleAclControl 17 }

		
		sleAclControlMatchFlags OBJECT-TYPE
			SYNTAX BITS
				{
				aclSrcIpAddress(0),
				aclSrcPrefixLength(1),
				aclDstIpAddress(2),
				aclDstPrefixLength(3),
				aclDscp(4),
				aclProtocolType(5),
				aclTcpFlag(6),
				aclSrcL4Port(7),
				aclDstL4Port(8),
				aclPacketLength(9)
				}
			MAX-ACCESS read-write
			STATUS current
			DESCRIPTION
				"Description"
			::= { sleAclControl 18 }

		
		sleAclControlMatchAction OBJECT-TYPE
			SYNTAX INTEGER
				{
				none(0),
				permit(1),
				deny(2)
				}
			MAX-ACCESS read-write
			STATUS current
			DESCRIPTION
				"Description"
			::= { sleAclControl 19 }

		
		sleAclControlNomatchAction OBJECT-TYPE
			SYNTAX INTEGER
				{
				none(0),
				permit(1),
				deny(2)
				}
			MAX-ACCESS read-write
			STATUS current
			DESCRIPTION
				"Description"
			::= { sleAclControl 20 }

		
		sleAclControlPriority OBJECT-TYPE
			SYNTAX INTEGER
				{
				low(1),
				medium(2),
				high(3),
				highest(4)
				}
			MAX-ACCESS read-write
			STATUS current
			DESCRIPTION
				"Description"
			::= { sleAclControl 21 }

		
		sleAclNotification OBJECT IDENTIFIER ::= { sleAcl 3 }

		
		sleAclCreated NOTIFICATION-TYPE
			OBJECTS { sleAclControlReqest, sleAclControlTimeStamp, sleAclControlReqResult, sleAclSrcIpAddr, sleAclSrcPrefixLength, 
				sleAclDstIpAddr, sleAclDstPrefixLength, sleAclDscp, sleAclProtocolType, sleAclTcpFlag, 
				sleAclSrcL4Port, sleAclDstL4Port, sleAclPktLen, sleAclValidFlags, sleAclMatchFlags, 
				sleAclMatchAction, sleAclNomatchAction, sleAclPriority }
			STATUS current
			DESCRIPTION 
				"Description"
			::= { sleAclNotification 1 }

		
		sleAclDestroyed NOTIFICATION-TYPE
			OBJECTS { sleAclControlReqest, sleAclControlTimeStamp, sleAclControlReqResult, sleAclControlName }
			STATUS current
			DESCRIPTION 
				"Description"
			::= { sleAclNotification 2 }

		
		sleAclClassifierProfileChanged NOTIFICATION-TYPE
			OBJECTS { sleAclControlReqest, sleAclControlTimeStamp, sleAclControlReqResult, sleAclSrcIpAddr, sleAclSrcPrefixLength, 
				sleAclDstIpAddr, sleAclDstPrefixLength, sleAclDscp, sleAclProtocolType, sleAclTcpFlag, 
				sleAclSrcL4Port, sleAclDstL4Port, sleAclPktLen, sleAclValidFlags, sleAclMatchFlags
				 }
			STATUS current
			DESCRIPTION 
				"Description"
			::= { sleAclNotification 3 }

		
		sleAclMatchActionChanged NOTIFICATION-TYPE
			OBJECTS { sleAclControlReqest, sleAclControlTimeStamp, sleAclControlReqResult, sleAclMatchAction }
			STATUS current
			DESCRIPTION 
				"Description"
			::= { sleAclNotification 4 }

		
		sleAclNomatchActionChanged NOTIFICATION-TYPE
			OBJECTS { sleAclControlReqest, sleAclControlTimeStamp, sleAclControlReqResult, sleAclNomatchAction }
			STATUS current
			DESCRIPTION 
				"Description"
			::= { sleAclNotification 5 }

		
		sleDot1xPort OBJECT IDENTIFIER ::= { sleSecurity 6 }

		
		sleDot1xPortTable OBJECT-TYPE
			SYNTAX SEQUENCE OF SleDot1xPortEntry
			MAX-ACCESS not-accessible
			STATUS current
			DESCRIPTION
				"The table that contains the configuration objects 
				for the Authenticator PAE associated with each port."
			::= { sleDot1xPort 1 }

		
		sleDot1xPortEntry OBJECT-TYPE
			SYNTAX SleDot1xPortEntry
			MAX-ACCESS not-accessible
			STATUS current
			DESCRIPTION
				"The configuration information for an Authenticator PAE."
			INDEX { sleDot1xPortIndex }
			::= { sleDot1xPortTable 1 }

		
		SleDot1xPortEntry ::=
			SEQUENCE { 
				sleDot1xPortIndex
					InterfaceIndex,
				sleDot1xPortEnable
					INTEGER,
				sleDot1xPortMode
					INTEGER,
				sleDot1xPortReauthEnable
					INTEGER,
				sleDot1xPortQuietPeriod
					Integer32,
				sleDot1xPortReauthPeriod
					Integer32,
				sleDot1xPortAuthSuccess
					INTEGER
			 }

		sleDot1xPortIndex OBJECT-TYPE
			SYNTAX InterfaceIndex
			MAX-ACCESS read-only
			STATUS current
			DESCRIPTION
				"The port number associated with this port."
			::= { sleDot1xPortEntry 1 }

		
		sleDot1xPortEnable OBJECT-TYPE
			SYNTAX INTEGER
				{
				disable(1),
				portEnable(2),
				macEnable(3)
				}
			MAX-ACCESS read-only
			STATUS current
			DESCRIPTION
				"The administrativ state for each port."
			::= { sleDot1xPortEntry 2 }

		
		sleDot1xPortMode OBJECT-TYPE
			SYNTAX INTEGER
				{
				default(-1),
				none(0),
				auto(1),
				forceAuthorized(2),
				forceUnauthorized(3)
				}
			MAX-ACCESS read-only
			STATUS current
			DESCRIPTION
				"The control values of the Authenticator PAE controlled."
			::= { sleDot1xPortEntry 3 }

		
		sleDot1xPortReauthEnable OBJECT-TYPE
			SYNTAX INTEGER
				{
				disable(0),
				enable(1)
				}
			MAX-ACCESS read-only
			STATUS current
			DESCRIPTION
				"The reauthentication control for this port."
			::= { sleDot1xPortEntry 4 }

		
		sleDot1xPortQuietPeriod OBJECT-TYPE
			SYNTAX Integer32 (1..65535)
			MAX-ACCESS read-only
			STATUS current
			DESCRIPTION
				"The value, in seconds, of the quietPeriod constant
				currently in use by the Authenticator PAE state machine."
			::= { sleDot1xPortEntry 5 }

		
		sleDot1xPortReauthPeriod OBJECT-TYPE
			SYNTAX Integer32 (1..65535)
			MAX-ACCESS read-only
			STATUS current
			DESCRIPTION
				"The value, in seconds, of the txPeriod constant
				currently in use by the Authenticator PAE state machine."
			::= { sleDot1xPortEntry 6 }

		
		sleDot1xPortAuthSuccess OBJECT-TYPE
			SYNTAX INTEGER
				{
				fail(1),
				success(2)
				}
			MAX-ACCESS read-only
			STATUS current
			DESCRIPTION
				"The value result to authentication of the supplicator."
			::= { sleDot1xPortEntry 7 }

		
		sleDot1xPortControl OBJECT IDENTIFIER ::= { sleDot1xPort 2 }

		
		sleDot1xPortControlRequest OBJECT-TYPE
			SYNTAX INTEGER
				{
				setDot1xPortProfile(1),
				setDot1xPortReauthenticate(2),
				setDot1xPortInittialize(3)
				}
			MAX-ACCESS read-write
			STATUS current
			DESCRIPTION
				"The MIB object for the dot1x command.A SetRequest 
				on this attribute starts a command execution 
				process in the netElement."
			::= { sleDot1xPortControl 1 }

		
		sleDot1xPortControlStatus OBJECT-TYPE
			SYNTAX SleControlStatusType
			MAX-ACCESS read-only
			STATUS current
			DESCRIPTION
				"Describes the status of a user command group, used
				for block commands while a command execution in process"
			::= { sleDot1xPortControl 2 }

		
		sleDot1xPortControlTimer OBJECT-TYPE
			SYNTAX Gauge32
			MAX-ACCESS read-write
			STATUS current
			DESCRIPTION
				"Maximum command duration time in case of long running."
			::= { sleDot1xPortControl 3 }

		
		sleDot1xPortControlTimeStamp OBJECT-TYPE
			SYNTAX TimeStamp
			MAX-ACCESS read-only
			STATUS current
			DESCRIPTION
				"Time stamp attribute set at end of command."
			::= { sleDot1xPortControl 4 }

		
		sleDot1xPortControlReqResult OBJECT-TYPE
			SYNTAX SleControlRequestResultType
			MAX-ACCESS read-only
			STATUS current
			DESCRIPTION
				"Command result attribute."
			::= { sleDot1xPortControl 5 }

		
		sleDot1xPortControlIndex OBJECT-TYPE
			SYNTAX Integer32
			MAX-ACCESS read-write
			STATUS current
			DESCRIPTION
				"The port number associated with this port."
			::= { sleDot1xPortControl 6 }

		
		sleDot1xPortControlEnable OBJECT-TYPE
			SYNTAX INTEGER
				{
				default(-1),
				disable(1),
				portEnable(2),
				macEnable(3)
				}
			MAX-ACCESS read-write
			STATUS current
			DESCRIPTION
				"The administrativ state for each port."
			::= { sleDot1xPortControl 7 }

		
		sleDot1xPortControlMode OBJECT-TYPE
			SYNTAX INTEGER
				{
				default(-1),
				none(0),
				auto(1),
				forceAuthorized(2),
				forceUnauthorized(3)
				}
			MAX-ACCESS read-write
			STATUS current
			DESCRIPTION
				"The control values of the Authenticator PAE controlled."
			::= { sleDot1xPortControl 8 }

		
		sleDot1xPortControlReauthEnable OBJECT-TYPE
			SYNTAX INTEGER
				{
				default(-1),
				disable(0),
				enable(1)
				}
			MAX-ACCESS read-write
			STATUS current
			DESCRIPTION
				"The reauthentication control for this port. Setting
				this attribute TRUE causes the Authenticator PAE state
				machine for the Port to reauthenticate the Supplicant.
				Setting this attribute FALSE has no effect."
			::= { sleDot1xPortControl 9 }

		
		sleDot1xPortControlQuietPeriod OBJECT-TYPE
			SYNTAX Integer32 (-1 | 1..65535)
			MAX-ACCESS read-write
			STATUS current
			DESCRIPTION
				"The value, in seconds, of the quietPeriod constant
				currently in use by the Authenticator PAE state machine."
			::= { sleDot1xPortControl 10 }

		
		sleDot1xPortControlReauthPeriod OBJECT-TYPE
			SYNTAX Integer32 (-1 | 1..65535)
			MAX-ACCESS read-write
			STATUS current
			DESCRIPTION
				"The value, in seconds, of the txPeriod constant
				currently in use by the Authenticator PAE state machine.
				(0~4294967295 for V5812G. 0 is initialization at 3600.)"
			::= { sleDot1xPortControl 11 }

		
		sleDot1xPortNotification OBJECT IDENTIFIER ::= { sleDot1xPort 3 }

		
		sleDot1xPortProfileChanged NOTIFICATION-TYPE
			OBJECTS { sleDot1xPortControlRequest, sleDot1xPortControlReqResult, sleDot1xPortControlTimeStamp, sleDot1xPortEnable, sleDot1xPortMode, 
				sleDot1xPortReauthEnable, sleDot1xPortQuietPeriod, sleDot1xPortReauthPeriod }
			STATUS current
			DESCRIPTION 
				"The trap for CLI command."
			::= { sleDot1xPortNotification 1 }

		
		sleDot1xPortAuthSuccessChanged NOTIFICATION-TYPE
			OBJECTS { sleDot1xPortControlRequest, sleDot1xPortControlTimeStamp, sleDot1xPortControlReqResult, sleDot1xPortAuthSuccess }
			STATUS current
			DESCRIPTION 
				"The trap for authentication result."
			::= { sleDot1xPortNotification 2 }

		
		sleDot1xStatistics OBJECT IDENTIFIER ::= { sleSecurity 7 }

		
		sleDot1xStatisticsTable OBJECT-TYPE
			SYNTAX SEQUENCE OF SleDot1xStatisticsEntry
			MAX-ACCESS not-accessible
			STATUS current
			DESCRIPTION
				"Description."
			::= { sleDot1xStatistics 1 }

		
		sleDot1xStatisticsEntry OBJECT-TYPE
			SYNTAX SleDot1xStatisticsEntry
			MAX-ACCESS not-accessible
			STATUS current
			DESCRIPTION
				"Description."
			INDEX { sleDot1xStatsPortIndex }
			::= { sleDot1xStatisticsTable 1 }

		
		SleDot1xStatisticsEntry ::=
			SEQUENCE { 
				sleDot1xStatsPortIndex
					INTEGER,
				sleDot1xStatsEapolFramesRx
					Counter32,
				sleDot1xStatsEapolFramesTx
					Counter32,
				sleDot1xStatsEapolStartFramesRx
					Counter32,
				sleDot1xStatsEapolLogoffFramesRx
					Counter32,
				sleDot1xStatsEapolRespIdFramesRx
					Counter32,
				sleDot1xStatsEapolRespFramesRx
					Counter32,
				sleDot1xStatsEapolReqIdFramesTx
					Counter32,
				sleDot1xStatsEapolReqFramesTx
					Integer32,
				sleDot1xStatsInvalidEapolFramesRx
					Counter32,
				sleDot1xStatsEapLengthErrorFramesRx
					Counter32,
				sleDot1xStatsLastEapolFrameVersion
					Counter32,
				sleDot1xStatsLastEapolFrameSource
					MacAddress
			 }

		sleDot1xStatsPortIndex OBJECT-TYPE
			SYNTAX INTEGER (1..255)
			MAX-ACCESS read-only
			STATUS current
			DESCRIPTION
				"Description"
			::= { sleDot1xStatisticsEntry 1 }

		
		sleDot1xStatsEapolFramesRx OBJECT-TYPE
			SYNTAX Counter32
			MAX-ACCESS read-only
			STATUS current
			DESCRIPTION
				"Description"
			::= { sleDot1xStatisticsEntry 2 }

		
		sleDot1xStatsEapolFramesTx OBJECT-TYPE
			SYNTAX Counter32
			MAX-ACCESS read-only
			STATUS current
			DESCRIPTION
				"Description"
			::= { sleDot1xStatisticsEntry 3 }

		
		sleDot1xStatsEapolStartFramesRx OBJECT-TYPE
			SYNTAX Counter32
			MAX-ACCESS read-only
			STATUS current
			DESCRIPTION
				"Description"
			::= { sleDot1xStatisticsEntry 4 }

		
		sleDot1xStatsEapolLogoffFramesRx OBJECT-TYPE
			SYNTAX Counter32
			MAX-ACCESS read-only
			STATUS current
			DESCRIPTION
				"Description"
			::= { sleDot1xStatisticsEntry 5 }

		
		sleDot1xStatsEapolRespIdFramesRx OBJECT-TYPE
			SYNTAX Counter32
			MAX-ACCESS read-only
			STATUS current
			DESCRIPTION
				"Description"
			::= { sleDot1xStatisticsEntry 6 }

		
		sleDot1xStatsEapolRespFramesRx OBJECT-TYPE
			SYNTAX Counter32
			MAX-ACCESS read-only
			STATUS current
			DESCRIPTION
				"Description"
			::= { sleDot1xStatisticsEntry 7 }

		
		sleDot1xStatsEapolReqIdFramesTx OBJECT-TYPE
			SYNTAX Counter32
			MAX-ACCESS read-only
			STATUS current
			DESCRIPTION
				"Description"
			::= { sleDot1xStatisticsEntry 8 }

		
		sleDot1xStatsEapolReqFramesTx OBJECT-TYPE
			SYNTAX Integer32
			MAX-ACCESS read-only
			STATUS current
			DESCRIPTION
				"Description"
			::= { sleDot1xStatisticsEntry 9 }

		
		sleDot1xStatsInvalidEapolFramesRx OBJECT-TYPE
			SYNTAX Counter32
			MAX-ACCESS read-only
			STATUS current
			DESCRIPTION
				"Description"
			::= { sleDot1xStatisticsEntry 10 }

		
		sleDot1xStatsEapLengthErrorFramesRx OBJECT-TYPE
			SYNTAX Counter32
			MAX-ACCESS read-only
			STATUS current
			DESCRIPTION
				"Description"
			::= { sleDot1xStatisticsEntry 11 }

		
		sleDot1xStatsLastEapolFrameVersion OBJECT-TYPE
			SYNTAX Counter32
			MAX-ACCESS read-only
			STATUS current
			DESCRIPTION
				"Description"
			::= { sleDot1xStatisticsEntry 12 }

		
		sleDot1xStatsLastEapolFrameSource OBJECT-TYPE
			SYNTAX MacAddress
			MAX-ACCESS read-only
			STATUS current
			DESCRIPTION
				"Description"
			::= { sleDot1xStatisticsEntry 13 }

		
		sleDot1xStatisticsControl OBJECT IDENTIFIER ::= { sleDot1xStatistics 2 }

		
		sleDot1xStatsControlRequest OBJECT-TYPE
			SYNTAX INTEGER { clearDot1xStatistics(1) }
			MAX-ACCESS read-write
			STATUS current
			DESCRIPTION
				"Description"
			::= { sleDot1xStatisticsControl 1 }

		
		sleDot1xStatsControlStatus OBJECT-TYPE
			SYNTAX SleControlStatusType
			MAX-ACCESS read-only
			STATUS current
			DESCRIPTION
				"Description"
			::= { sleDot1xStatisticsControl 2 }

		
		sleDot1xStatsControlTimer OBJECT-TYPE
			SYNTAX Gauge32
			MAX-ACCESS read-write
			STATUS current
			DESCRIPTION
				"Description"
			::= { sleDot1xStatisticsControl 3 }

		
		sleDot1xStatsControlTimeStamp OBJECT-TYPE
			SYNTAX TimeTicks
			MAX-ACCESS read-only
			STATUS current
			DESCRIPTION
				"Description"
			::= { sleDot1xStatisticsControl 4 }

		
		sleDot1xStatsControlReqResult OBJECT-TYPE
			SYNTAX SleControlRequestResultType
			MAX-ACCESS read-only
			STATUS current
			DESCRIPTION
				"Description"
			::= { sleDot1xStatisticsControl 5 }

		
		sleDot1xStatsControlPortIndex OBJECT-TYPE
			SYNTAX Unsigned32 (1..255)
			MAX-ACCESS read-write
			STATUS current
			DESCRIPTION
				"Description"
			::= { sleDot1xStatisticsControl 6 }

		
		sleDot1xStatisticsNotification OBJECT IDENTIFIER ::= { sleDot1xStatistics 3 }

		
		sleDot1xStatisticsCleared NOTIFICATION-TYPE
			OBJECTS { sleDot1xStatsControlRequest, sleDot1xStatsControlTimeStamp, sleDot1xStatsControlReqResult, sleDot1xStatsControlPortIndex }
			STATUS current
			DESCRIPTION 
				"Description"
			::= { sleDot1xStatisticsNotification 1 }

		
		sleArpInspection OBJECT IDENTIFIER ::= { sleSecurity 8 }

		
		sleArpInspectBase OBJECT IDENTIFIER ::= { sleArpInspection 1 }

		
		sleArpInspectBaseInfo OBJECT IDENTIFIER ::= { sleArpInspectBase 1 }

		
		sleArpInspectValidateSrcMac OBJECT-TYPE
			SYNTAX INTEGER
				{
				disable(0),
				enable(1)
				}
			MAX-ACCESS read-only
			STATUS current
			DESCRIPTION
				"Validate Source Mac"
			::= { sleArpInspectBaseInfo 1 }

		
		sleArpInspectValidateDstMac OBJECT-TYPE
			SYNTAX INTEGER
				{
				disable(0),
				enable(1)
				}
			MAX-ACCESS read-only
			STATUS current
			DESCRIPTION
				"Validate Destination Mac"
			::= { sleArpInspectBaseInfo 2 }

		
		sleArpInspectValidateIpAddr OBJECT-TYPE
			SYNTAX INTEGER
				{
				disable(0),
				enable(1)
				}
			MAX-ACCESS read-only
			STATUS current
			DESCRIPTION
				"Validate IP Address"
			::= { sleArpInspectBaseInfo 3 }

		
		sleArpInspectLogBufferSize OBJECT-TYPE
			SYNTAX Integer32 (0..1024)
			MAX-ACCESS read-only
			STATUS current
			DESCRIPTION
				"Description."
			::= { sleArpInspectBaseInfo 4 }

		
		sleArpInspectLogEntry OBJECT-TYPE
			SYNTAX Integer32 (0..1024)
			MAX-ACCESS read-only
			STATUS current
			DESCRIPTION
				"Description."
			::= { sleArpInspectBaseInfo 5 }

		
		sleArpInspectLogInterval OBJECT-TYPE
			SYNTAX Integer32 (0..86400)
			MAX-ACCESS read-only
			STATUS current
			DESCRIPTION
				"Description."
			::= { sleArpInspectBaseInfo 6 }

		
		sleArpInspectBaseControl OBJECT IDENTIFIER ::= { sleArpInspectBase 2 }

		
		sleArpInspectControlRequest OBJECT-TYPE
			SYNTAX INTEGER
				{
				setArpInspectValidateProfile(1),
				setArpInspectLogBufferSize(2),
				setArpInspectLogRate(3)
				}
			MAX-ACCESS read-write
			STATUS current
			DESCRIPTION
				"Description"
			::= { sleArpInspectBaseControl 1 }

		
		sleArpInspectControlStatus OBJECT-TYPE
			SYNTAX SleControlStatusType
			MAX-ACCESS read-only
			STATUS current
			DESCRIPTION
				"Description"
			::= { sleArpInspectBaseControl 2 }

		
		sleArpInspectControlTimer OBJECT-TYPE
			SYNTAX Gauge32
			MAX-ACCESS read-write
			STATUS current
			DESCRIPTION
				"Description"
			::= { sleArpInspectBaseControl 3 }

		
		sleArpInspectControlTimeStamp OBJECT-TYPE
			SYNTAX TimeTicks
			MAX-ACCESS read-only
			STATUS current
			DESCRIPTION
				"Description"
			::= { sleArpInspectBaseControl 4 }

		
		sleArpInspectControlReqResult OBJECT-TYPE
			SYNTAX SleControlRequestResultType
			MAX-ACCESS read-only
			STATUS current
			DESCRIPTION
				"Result of the last command."
			::= { sleArpInspectBaseControl 5 }

		
		sleArpInspectControlValidateSrcMac OBJECT-TYPE
			SYNTAX INTEGER
				{
				disable(0),
				enable(1)
				}
			MAX-ACCESS read-write
			STATUS current
			DESCRIPTION
				"Description."
			::= { sleArpInspectBaseControl 6 }

		
		sleArpInspectControlValidateDstMac OBJECT-TYPE
			SYNTAX INTEGER
				{
				disable(0),
				enable(1)
				}
			MAX-ACCESS read-write
			STATUS current
			DESCRIPTION
				"Description."
			::= { sleArpInspectBaseControl 7 }

		
		sleArpInspectControlValidateIpAddr OBJECT-TYPE
			SYNTAX INTEGER
				{
				disable(0),
				enable(1)
				}
			MAX-ACCESS read-write
			STATUS current
			DESCRIPTION
				"Description."
			::= { sleArpInspectBaseControl 8 }

		
		sleArpInspectControlLogBufferSize OBJECT-TYPE
			SYNTAX Integer32 (0..1024)
			MAX-ACCESS read-write
			STATUS current
			DESCRIPTION
				"Description."
			::= { sleArpInspectBaseControl 9 }

		
		sleArpInspectControlLogEntry OBJECT-TYPE
			SYNTAX Integer32 (0..1024)
			MAX-ACCESS read-write
			STATUS current
			DESCRIPTION
				"Description."
			::= { sleArpInspectBaseControl 10 }

		
		sleArpInspectControlLogInterval OBJECT-TYPE
			SYNTAX Integer32 (0..86400)
			MAX-ACCESS read-write
			STATUS current
			DESCRIPTION
				"Description."
			::= { sleArpInspectBaseControl 11 }

		
		sleArpInspectBaseNotifications OBJECT IDENTIFIER ::= { sleArpInspectBase 3 }

		
		sleArpInspectValidateChanged NOTIFICATION-TYPE
			OBJECTS { sleArpInspectControlRequest, sleArpInspectControlTimeStamp, sleArpInspectControlReqResult, sleArpInspectControlValidateSrcMac, sleArpInspectControlValidateDstMac, 
				sleArpInspectControlValidateIpAddr }
			STATUS current
			DESCRIPTION 
				"sleArpInspectValidateControl"
			::= { sleArpInspectBaseNotifications 1 }

		
		sleArpInspectLogBufferSizeChanged NOTIFICATION-TYPE
			OBJECTS { sleArpInspectControlRequest, sleArpInspectControlTimeStamp, sleArpInspectControlReqResult, sleArpInspectControlLogBufferSize }
			STATUS current
			DESCRIPTION 
				"Description."
			::= { sleArpInspectBaseNotifications 2 }

		
		sleArpInspectLogRateChanged NOTIFICATION-TYPE
			OBJECTS { sleArpInspectControlRequest, sleArpInspectControlTimeStamp, sleArpInspectControlReqResult, sleArpInspectControlLogEntry, sleArpInspectControlLogInterval
				 }
			STATUS current
			DESCRIPTION 
				"Description."
			::= { sleArpInspectBaseNotifications 3 }

		
		sleArpACL OBJECT IDENTIFIER ::= { sleArpInspection 2 }

		
		sleArpAclTable OBJECT-TYPE
			SYNTAX SEQUENCE OF SleArpAclEntry
			MAX-ACCESS not-accessible
			STATUS current
			DESCRIPTION
				"Description."
			::= { sleArpACL 1 }

		
		sleArpAclEntry OBJECT-TYPE
			SYNTAX SleArpAclEntry
			MAX-ACCESS not-accessible
			STATUS current
			DESCRIPTION
				"Description."
			INDEX { sleArpAclIndex }
			::= { sleArpAclTable 1 }

		
		SleArpAclEntry ::=
			SEQUENCE { 
				sleArpAclIndex
					INTEGER,
				sleArpAclName
					OCTET STRING,
				sleArpAclNumEntries
					INTEGER
			 }

		sleArpAclIndex OBJECT-TYPE
			SYNTAX INTEGER (1..2147483647)
			MAX-ACCESS read-only
			STATUS current
			DESCRIPTION
				"Description."
			::= { sleArpAclEntry 1 }

		
		sleArpAclName OBJECT-TYPE
			SYNTAX OCTET STRING (SIZE (1..255))
			MAX-ACCESS read-only
			STATUS current
			DESCRIPTION
				"Description."
			::= { sleArpAclEntry 2 }

		
		sleArpAclNumEntries OBJECT-TYPE
			SYNTAX INTEGER (1..2147483647)
			MAX-ACCESS read-only
			STATUS current
			DESCRIPTION
				"Number of Entries"
			::= { sleArpAclEntry 3 }

		
		sleArpAclControl OBJECT IDENTIFIER ::= { sleArpACL 2 }

		
		sleArpAclControlRequest OBJECT-TYPE
			SYNTAX INTEGER
				{
				createArpAcl(1),
				destroyArpAcl(2)
				}
			MAX-ACCESS read-write
			STATUS current
			DESCRIPTION
				"Description"
			::= { sleArpAclControl 1 }

		
		sleArpAclControlStatus OBJECT-TYPE
			SYNTAX SleControlStatusType
			MAX-ACCESS read-only
			STATUS current
			DESCRIPTION
				"Description"
			::= { sleArpAclControl 2 }

		
		sleArpAclControlTimer OBJECT-TYPE
			SYNTAX Gauge32
			MAX-ACCESS read-write
			STATUS current
			DESCRIPTION
				"Description"
			::= { sleArpAclControl 3 }

		
		sleArpAclControlTimeStamp OBJECT-TYPE
			SYNTAX TimeTicks
			MAX-ACCESS read-only
			STATUS current
			DESCRIPTION
				"Description"
			::= { sleArpAclControl 4 }

		
		sleArpAclControlReqResult OBJECT-TYPE
			SYNTAX SleControlRequestResultType
			MAX-ACCESS read-only
			STATUS current
			DESCRIPTION
				"Result of the last command."
			::= { sleArpAclControl 5 }

		
		sleArpAclControlIndex OBJECT-TYPE
			SYNTAX Integer32
			MAX-ACCESS read-write
			STATUS current
			DESCRIPTION
				"Description."
			::= { sleArpAclControl 6 }

		
		sleArpAclControlName OBJECT-TYPE
			SYNTAX OCTET STRING (SIZE (1..255))
			MAX-ACCESS read-write
			STATUS current
			DESCRIPTION
				"The name of acl."
			::= { sleArpAclControl 7 }

		
		sleArpAclNotifications OBJECT IDENTIFIER ::= { sleArpACL 3 }

		
		sleArpAclCreated NOTIFICATION-TYPE
			OBJECTS { sleArpAclControlRequest, sleArpAclControlTimeStamp, sleArpAclControlReqResult, sleArpAclName }
			STATUS current
			DESCRIPTION 
				"sleArpInspectValidateControl"
			::= { sleArpAclNotifications 1 }

		
		sleArpAclDestroyed NOTIFICATION-TYPE
			OBJECTS { sleArpAclControlRequest, sleArpAclControlTimeStamp, sleArpAclControlReqResult, sleArpAclControlIndex }
			STATUS current
			DESCRIPTION 
				"sleArpInspectValidateControl"
			::= { sleArpAclNotifications 2 }

		
		sleArpACLRule OBJECT IDENTIFIER ::= { sleArpInspection 3 }

		
		sleArpAclRuleTable OBJECT-TYPE
			SYNTAX SEQUENCE OF SleArpAclRuleEntry
			MAX-ACCESS not-accessible
			STATUS current
			DESCRIPTION
				"Description."
			::= { sleArpACLRule 1 }

		
		sleArpAclRuleEntry OBJECT-TYPE
			SYNTAX SleArpAclRuleEntry
			MAX-ACCESS not-accessible
			STATUS current
			DESCRIPTION
				"Description."
			INDEX { sleArpAclRuleAclIndex, sleArpAclRuleIndex }
			::= { sleArpAclRuleTable 1 }

		
		SleArpAclRuleEntry ::=
			SEQUENCE { 
				sleArpAclRuleAclIndex
					Integer32,
				sleArpAclRuleIndex
					Integer32,
				sleArpAclRuleAction
					INTEGER,
				sleArpAclRuleType
					INTEGER,
				sleArpAclRuleRangeStartIP
					IpAddress,
				sleArpAclRuleRangeEndIP
					IpAddress,
				sleArpAclRuleIPAddress
					IpAddress,
				sleArpAclRuleIPMask
					Integer32,
				sleArpAclRuleMacAddr
					MacAddress,
				sleArpAclRuleMacType
					INTEGER
			 }

		sleArpAclRuleAclIndex OBJECT-TYPE
			SYNTAX Integer32 (1..2147483647)
			MAX-ACCESS read-only
			STATUS current
			DESCRIPTION
				"Description."
			::= { sleArpAclRuleEntry 1 }

		
		sleArpAclRuleIndex OBJECT-TYPE
			SYNTAX Integer32 (1..2147483647)
			MAX-ACCESS read-only
			STATUS current
			DESCRIPTION
				"ACL entry Index"
			::= { sleArpAclRuleEntry 2 }

		
		sleArpAclRuleAction OBJECT-TYPE
			SYNTAX INTEGER
				{
				deny(0),
				permit(1)
				}
			MAX-ACCESS read-only
			STATUS current
			DESCRIPTION
				"The permit/deny control used per entry"
			::= { sleArpAclRuleEntry 3 }

		
		sleArpAclRuleType OBJECT-TYPE
			SYNTAX INTEGER
				{
				subnet(0),
				range(1),
				dhcpSnooping(2)
				}
			MAX-ACCESS read-only
			STATUS current
			DESCRIPTION
				"Specify IP address is host or range."
			::= { sleArpAclRuleEntry 4 }

		
		sleArpAclRuleRangeStartIP OBJECT-TYPE
			SYNTAX IpAddress
			MAX-ACCESS read-only
			STATUS current
			DESCRIPTION
				"Valid if sleArpAclEntryRange is 1,Otherwise this value is invalid."
			::= { sleArpAclRuleEntry 5 }

		
		sleArpAclRuleRangeEndIP OBJECT-TYPE
			SYNTAX IpAddress
			MAX-ACCESS read-only
			STATUS current
			DESCRIPTION
				"Valid if sleArpAclEntryRange is 1,Otherwise this value is invalid."
			::= { sleArpAclRuleEntry 6 }

		
		sleArpAclRuleIPAddress OBJECT-TYPE
			SYNTAX IpAddress
			MAX-ACCESS read-only
			STATUS current
			DESCRIPTION
				"IP Address.Valid if sleArpAclEntryRange is 0."
			::= { sleArpAclRuleEntry 7 }

		
		sleArpAclRuleIPMask OBJECT-TYPE
			SYNTAX Integer32 (1..32)
			MAX-ACCESS read-only
			STATUS current
			DESCRIPTION
				"SubnetMask.Valid if sleArpAclEntryRange is 0."
			::= { sleArpAclRuleEntry 8 }

		
		sleArpAclRuleMacAddr OBJECT-TYPE
			SYNTAX MacAddress
			MAX-ACCESS read-only
			STATUS current
			DESCRIPTION
				"Mac Address. If  sleArpAclEntryMacType is 0 , this value is invalid."
			::= { sleArpAclRuleEntry 9 }

		
		sleArpAclRuleMacType OBJECT-TYPE
			SYNTAX INTEGER
				{
				any(0),
				host(1)
				}
			MAX-ACCESS read-only
			STATUS current
			DESCRIPTION
				"Description."
			::= { sleArpAclRuleEntry 10 }

		
		sleArpAclRuleControl OBJECT IDENTIFIER ::= { sleArpACLRule 2 }

		
		sleArpAclRuleControlRequest OBJECT-TYPE
			SYNTAX INTEGER
				{
				createArpAclRule(1),
				destroyArpAclRule(2)
				}
			MAX-ACCESS read-write
			STATUS current
			DESCRIPTION
				"Description"
			::= { sleArpAclRuleControl 1 }

		
		sleArpAclRuleControlStatus OBJECT-TYPE
			SYNTAX SleControlStatusType
			MAX-ACCESS read-only
			STATUS current
			DESCRIPTION
				"Description"
			::= { sleArpAclRuleControl 2 }

		
		sleArpAclRuleControlTimer OBJECT-TYPE
			SYNTAX Gauge32
			MAX-ACCESS read-write
			STATUS current
			DESCRIPTION
				"Description"
			::= { sleArpAclRuleControl 3 }

		
		sleArpAclRuleControlTimeStamp OBJECT-TYPE
			SYNTAX TimeTicks
			MAX-ACCESS read-only
			STATUS current
			DESCRIPTION
				"Description"
			::= { sleArpAclRuleControl 4 }

		
		sleArpAclRuleControlReqResult OBJECT-TYPE
			SYNTAX SleControlRequestResultType
			MAX-ACCESS read-only
			STATUS current
			DESCRIPTION
				"Result of the last command."
			::= { sleArpAclRuleControl 5 }

		
		sleArpAclRuleControlAclIndex OBJECT-TYPE
			SYNTAX Integer32
			MAX-ACCESS read-write
			STATUS current
			DESCRIPTION
				"The name of acl."
			::= { sleArpAclRuleControl 6 }

		
		sleArpAclRuleControlIndex OBJECT-TYPE
			SYNTAX Integer32
			MAX-ACCESS read-write
			STATUS current
			DESCRIPTION
				"The entry index within ACL"
			::= { sleArpAclRuleControl 7 }

		
		sleArpAclRuleControlAction OBJECT-TYPE
			SYNTAX INTEGER
				{
				deny(0),
				permit(1)
				}
			MAX-ACCESS read-write
			STATUS current
			DESCRIPTION
				"The permit/deny control used per entry"
			::= { sleArpAclRuleControl 8 }

		
		sleArpAclRuleControlType OBJECT-TYPE
			SYNTAX INTEGER
				{
				subnet(0),
				range(1),
				dhcpSnooping(2)
				}
			MAX-ACCESS read-write
			STATUS current
			DESCRIPTION
				"If  type of entry is 1, sleArpAclEntryControlType must be 0.
				"
			::= { sleArpAclRuleControl 9 }

		
		sleArpAclRuleControlRangeStartIP OBJECT-TYPE
			SYNTAX IpAddress
			MAX-ACCESS read-write
			STATUS current
			DESCRIPTION
				"Description"
			::= { sleArpAclRuleControl 10 }

		
		sleArpAclRuleControlRangeEndIP OBJECT-TYPE
			SYNTAX IpAddress
			MAX-ACCESS read-write
			STATUS current
			DESCRIPTION
				"Description"
			::= { sleArpAclRuleControl 11 }

		
		sleArpAclRuleControlIPAddress OBJECT-TYPE
			SYNTAX IpAddress
			MAX-ACCESS read-write
			STATUS current
			DESCRIPTION
				"Description"
			::= { sleArpAclRuleControl 12 }

		
		sleArpAclRuleControlIPMask OBJECT-TYPE
			SYNTAX INTEGER (1..32)
			MAX-ACCESS read-write
			STATUS current
			DESCRIPTION
				"Description"
			::= { sleArpAclRuleControl 13 }

		
		sleArpAclRuleControlMacAddr OBJECT-TYPE
			SYNTAX MacAddress
			MAX-ACCESS read-write
			STATUS current
			DESCRIPTION
				"Description"
			::= { sleArpAclRuleControl 14 }

		
		sleArpAclRuleControlMacType OBJECT-TYPE
			SYNTAX INTEGER
				{
				any(0),
				host(1)
				}
			MAX-ACCESS read-write
			STATUS current
			DESCRIPTION
				"Description"
			::= { sleArpAclRuleControl 15 }

		
		sleArpAclRuleNotifications OBJECT IDENTIFIER ::= { sleArpACLRule 3 }

		
		sleArpAclRuleCreated NOTIFICATION-TYPE
			OBJECTS { sleArpAclRuleControlRequest, sleArpAclRuleControlTimeStamp, sleArpAclRuleControlReqResult, sleArpAclRuleAction, sleArpAclRuleType, 
				sleArpAclRuleRangeStartIP, sleArpAclRuleRangeEndIP, sleArpAclRuleIPAddress, sleArpAclRuleIPMask, sleArpAclRuleMacAddr, 
				sleArpAclRuleMacType }
			STATUS current
			DESCRIPTION 
				"createArpAclEntry"
			::= { sleArpAclRuleNotifications 1 }

		
		sleArpAclRuleDestroyed NOTIFICATION-TYPE
			OBJECTS { sleArpAclRuleControlRequest, sleArpAclRuleControlTimeStamp, sleArpAclRuleControlReqResult, sleArpAclRuleControlAclIndex, sleArpAclRuleControlIndex
				 }
			STATUS current
			DESCRIPTION 
				"destroyArpAclEntry"
			::= { sleArpAclRuleNotifications 2 }

		
		sleArpInspectVlan OBJECT IDENTIFIER ::= { sleArpInspection 4 }

		
		sleArpInspectVlanTable OBJECT-TYPE
			SYNTAX SEQUENCE OF SleArpInspectVlanEntry
			MAX-ACCESS not-accessible
			STATUS current
			DESCRIPTION
				"Description."
			::= { sleArpInspectVlan 1 }

		
		sleArpInspectVlanEntry OBJECT-TYPE
			SYNTAX SleArpInspectVlanEntry
			MAX-ACCESS not-accessible
			STATUS current
			DESCRIPTION
				"Description."
			INDEX { sleArpInspectVlanIndex }
			::= { sleArpInspectVlanTable 1 }

		
		SleArpInspectVlanEntry ::=
			SEQUENCE { 
				sleArpInspectVlanIndex
					Integer32,
				sleArpInspectVlanEnable
					INTEGER,
				sleArpInspectVlanFilterAcl
					Integer32,
				sleArpInspectVlanFwdPktCnt
					Integer32,
				sleArpInspectVlanDropPktCnt
					Integer32,
				sleArpInspectVlanAclPermits
					Integer32,
				sleArpInspectVlanAclDrops
					Integer32,
				sleArpInspectVlanSrcMacFailurs
					Integer32,
				sleArpInspectVlanDstMacFailurs
					Integer32,
				sleArpInspectVlanIpAddrFailurs
					Integer32,
				sleArpInspectVlanFilterAclName
					OCTET STRING
			 }

		sleArpInspectVlanIndex OBJECT-TYPE
			SYNTAX Integer32 (1..4094)
			MAX-ACCESS read-only
			STATUS current
			DESCRIPTION
				"The index of vlan."
			::= { sleArpInspectVlanEntry 1 }

		
		sleArpInspectVlanEnable OBJECT-TYPE
			SYNTAX INTEGER
				{
				disable(0),
				enable(1)
				}
			MAX-ACCESS read-only
			STATUS current
			DESCRIPTION
				"The enable/disable control used per vlan."
			::= { sleArpInspectVlanEntry 2 }

		
		sleArpInspectVlanFilterAcl OBJECT-TYPE
			SYNTAX Integer32
			MAX-ACCESS read-only
			STATUS current
			DESCRIPTION
				"Description."
			::= { sleArpInspectVlanEntry 3 }

		
		sleArpInspectVlanFwdPktCnt OBJECT-TYPE
			SYNTAX Integer32
			MAX-ACCESS read-only
			STATUS current
			DESCRIPTION
				"Forwarded arp packet count."
			::= { sleArpInspectVlanEntry 4 }

		
		sleArpInspectVlanDropPktCnt OBJECT-TYPE
			SYNTAX Integer32
			MAX-ACCESS read-only
			STATUS current
			DESCRIPTION
				"Droped arp packet count."
			::= { sleArpInspectVlanEntry 5 }

		
		sleArpInspectVlanAclPermits OBJECT-TYPE
			SYNTAX Integer32
			MAX-ACCESS read-only
			STATUS current
			DESCRIPTION
				"Description."
			::= { sleArpInspectVlanEntry 6 }

		
		sleArpInspectVlanAclDrops OBJECT-TYPE
			SYNTAX Integer32
			MAX-ACCESS read-only
			STATUS current
			DESCRIPTION
				"Description."
			::= { sleArpInspectVlanEntry 7 }

		
		sleArpInspectVlanSrcMacFailurs OBJECT-TYPE
			SYNTAX Integer32
			MAX-ACCESS read-only
			STATUS current
			DESCRIPTION
				"Description."
			::= { sleArpInspectVlanEntry 8 }

		
		sleArpInspectVlanDstMacFailurs OBJECT-TYPE
			SYNTAX Integer32
			MAX-ACCESS read-only
			STATUS current
			DESCRIPTION
				"Description."
			::= { sleArpInspectVlanEntry 9 }

		
		sleArpInspectVlanIpAddrFailurs OBJECT-TYPE
			SYNTAX Integer32
			MAX-ACCESS read-only
			STATUS current
			DESCRIPTION
				"Description."
			::= { sleArpInspectVlanEntry 10 }

		
		sleArpInspectVlanFilterAclName OBJECT-TYPE
			SYNTAX OCTET STRING (SIZE (1..255))
			MAX-ACCESS read-only
			STATUS current
			DESCRIPTION
				"Description."
			::= { sleArpInspectVlanEntry 11 }

		
		sleArpInspectVlanControl OBJECT IDENTIFIER ::= { sleArpInspectVlan 2 }

		
		sleArpInspectVlanControlRequest OBJECT-TYPE
			SYNTAX INTEGER
				{
				setArpInspectVlanProfile(1),
				clearArpInspectVlanStatistics(2)
				}
			MAX-ACCESS read-write
			STATUS current
			DESCRIPTION
				"Description"
			::= { sleArpInspectVlanControl 1 }

		
		sleArpInspectVlanControlStatus OBJECT-TYPE
			SYNTAX SleControlStatusType
			MAX-ACCESS read-only
			STATUS current
			DESCRIPTION
				"Description"
			::= { sleArpInspectVlanControl 2 }

		
		sleArpInspectVlanControlTimer OBJECT-TYPE
			SYNTAX Gauge32
			MAX-ACCESS read-write
			STATUS current
			DESCRIPTION
				"Description"
			::= { sleArpInspectVlanControl 3 }

		
		sleArpInspectVlanControlTimeStamp OBJECT-TYPE
			SYNTAX TimeTicks
			MAX-ACCESS read-only
			STATUS current
			DESCRIPTION
				"Description"
			::= { sleArpInspectVlanControl 4 }

		
		sleArpInspectVlanControlReqResult OBJECT-TYPE
			SYNTAX SleControlRequestResultType
			MAX-ACCESS read-only
			STATUS current
			DESCRIPTION
				"Result of the last command."
			::= { sleArpInspectVlanControl 5 }

		
		sleArpInspectVlanControlIndex OBJECT-TYPE
			SYNTAX INTEGER (1..4094)
			MAX-ACCESS read-write
			STATUS current
			DESCRIPTION
				"The index of vlan."
			::= { sleArpInspectVlanControl 6 }

		
		sleArpInspectVlanControlEnable OBJECT-TYPE
			SYNTAX INTEGER
				{
				disable(0),
				enable(1)
				}
			MAX-ACCESS read-write
			STATUS current
			DESCRIPTION
				"The enable/disable control used per vlan."
			::= { sleArpInspectVlanControl 7 }

		
		sleArpInspectVlanControlFilterAcl OBJECT-TYPE
			SYNTAX Integer32
			MAX-ACCESS read-write
			STATUS current
			DESCRIPTION
				"The ARP Access-list Name to be applied to vlan"
			::= { sleArpInspectVlanControl 8 }

		
		sleArpInspectVlanNotifications OBJECT IDENTIFIER ::= { sleArpInspectVlan 3 }

		
		sleArpInspectVlanChanged NOTIFICATION-TYPE
			OBJECTS { sleArpInspectVlanControlRequest, sleArpInspectVlanControlTimeStamp, sleArpInspectVlanControlReqResult, sleArpInspectVlanEnable, sleArpInspectVlanFilterAcl
				 }
			STATUS current
			DESCRIPTION 
				"setArpInspectVlanProfile"
			::= { sleArpInspectVlanNotifications 1 }

		
		sleArpInspectPort OBJECT IDENTIFIER ::= { sleArpInspection 5 }

		
		sleArpInspectPortTable OBJECT-TYPE
			SYNTAX SEQUENCE OF SleArpInspectPortEntry
			MAX-ACCESS not-accessible
			STATUS current
			DESCRIPTION
				"Description."
			::= { sleArpInspectPort 1 }

		
		sleArpInspectPortEntry OBJECT-TYPE
			SYNTAX SleArpInspectPortEntry
			MAX-ACCESS not-accessible
			STATUS current
			DESCRIPTION
				"Description."
			INDEX { sleArpInspectPortIndex }
			::= { sleArpInspectPortTable 1 }

		
		SleArpInspectPortEntry ::=
			SEQUENCE { 
				sleArpInspectPortIndex
					Integer32,
				sleArpInspectPortTrust
					INTEGER
			 }

		sleArpInspectPortIndex OBJECT-TYPE
			SYNTAX Integer32 (1..255)
			MAX-ACCESS read-only
			STATUS current
			DESCRIPTION
				"The index of port."
			::= { sleArpInspectPortEntry 1 }

		
		sleArpInspectPortTrust OBJECT-TYPE
			SYNTAX INTEGER
				{
				untrust(0),
				trust(1)
				}
			MAX-ACCESS read-only
			STATUS current
			DESCRIPTION
				"The trust/untrust control used per port."
			::= { sleArpInspectPortEntry 2 }

		
		sleArpInspectPortControl OBJECT IDENTIFIER ::= { sleArpInspectPort 2 }

		
		sleArpInspectPortControlRequest OBJECT-TYPE
			SYNTAX INTEGER { setArpInspectTrustPort(1) }
			MAX-ACCESS read-write
			STATUS current
			DESCRIPTION
				"Description"
			::= { sleArpInspectPortControl 1 }

		
		sleArpInspectPortControlStatus OBJECT-TYPE
			SYNTAX SleControlStatusType
			MAX-ACCESS read-only
			STATUS current
			DESCRIPTION
				"Description"
			::= { sleArpInspectPortControl 2 }

		
		sleArpInspectPortControlTimer OBJECT-TYPE
			SYNTAX Gauge32
			MAX-ACCESS read-write
			STATUS current
			DESCRIPTION
				"Description"
			::= { sleArpInspectPortControl 3 }

		
		sleArpInspectPortControlTimeStamp OBJECT-TYPE
			SYNTAX TimeTicks
			MAX-ACCESS read-only
			STATUS current
			DESCRIPTION
				"Description"
			::= { sleArpInspectPortControl 4 }

		
		sleArpInspectPortControlReqResult OBJECT-TYPE
			SYNTAX SleControlRequestResultType
			MAX-ACCESS read-only
			STATUS current
			DESCRIPTION
				"Result of the last command."
			::= { sleArpInspectPortControl 5 }

		
		sleArpInspectPortControlIndex OBJECT-TYPE
			SYNTAX INTEGER (1..255)
			MAX-ACCESS read-write
			STATUS current
			DESCRIPTION
				"The index of port."
			::= { sleArpInspectPortControl 6 }

		
		sleArpInspectPortControlTrust OBJECT-TYPE
			SYNTAX INTEGER
				{
				untrust(0),
				trust(1)
				}
			MAX-ACCESS read-write
			STATUS current
			DESCRIPTION
				"The enable/disable control used per port"
			::= { sleArpInspectPortControl 7 }

		
		sleArpInspectPortNotifications OBJECT IDENTIFIER ::= { sleArpInspectPort 3 }

		
		sleArpInspectPortChanged NOTIFICATION-TYPE
			OBJECTS { sleArpInspectPortControlRequest, sleArpInspectPortControlTimeStamp, sleArpInspectPortControlTrust, sleArpInspectPortControlReqResult }
			STATUS current
			DESCRIPTION 
				"setArpInspectTrustPort"
			::= { sleArpInspectPortNotifications 1 }

		
		sleArpInspectInvalidLog OBJECT IDENTIFIER ::= { sleArpInspection 6 }

		
		sleArpInspectInvalidLogTable OBJECT-TYPE
			SYNTAX SEQUENCE OF SleArpInspectInvalidLogEntry
			MAX-ACCESS not-accessible
			STATUS current
			DESCRIPTION
				"Description."
			::= { sleArpInspectInvalidLog 1 }

		
		sleArpInspectInvalidLogEntry OBJECT-TYPE
			SYNTAX SleArpInspectInvalidLogEntry
			MAX-ACCESS not-accessible
			STATUS current
			DESCRIPTION
				"Description."
			INDEX { sleArpInspectInvalidLogId }
			::= { sleArpInspectInvalidLogTable 1 }

		
		SleArpInspectInvalidLogEntry ::=
			SEQUENCE { 
				sleArpInspectInvalidLogId
					INTEGER,
				sleArpInspectInvalidLogReason
					INTEGER,
				sleArpInspectInvalidLogSamePktCnt
					Counter32,
				sleArpInspectInvalidLogOpcode
					INTEGER,
				sleArpInspectInvalidLogPortNumber
					INTEGER,
				sleArpInspectInvalidLogVlanId
					INTEGER,
				sleArpInspectInvalidLogSrcMacAddr
					OCTET STRING,
				sleArpInspectInvalidLogSrcIpAddr
					IpAddress,
				sleArpInspectInvalidLogDstMacAddr
					OCTET STRING,
				sleArpInspectInvalidLogDstIpAddr
					IpAddress,
				sleArpInspectInvalidLogLastRecvTime
					OCTET STRING
			 }

		sleArpInspectInvalidLogId OBJECT-TYPE
			SYNTAX INTEGER (0..65535)
			MAX-ACCESS read-only
			STATUS current
			DESCRIPTION
				"ARP inspection invalid index."
			::= { sleArpInspectInvalidLogEntry 1 }

		
		sleArpInspectInvalidLogReason OBJECT-TYPE
			SYNTAX INTEGER
				{
				aliReasonNone(0),
				aliReasonDhcpPermit(1),
				aliReasonDhcpDeny(2),
				aliReasonAclPermit(3),
				aliReasonAclDeny(4),
				aliReasonValidSrcfail(5),
				aliReasonValidDstfail(6),
				aliReasonValidIpfail(7)
				}
			MAX-ACCESS read-only
			STATUS current
			DESCRIPTION
				"ARP inspection invalid reason."
			::= { sleArpInspectInvalidLogEntry 2 }

		
		sleArpInspectInvalidLogSamePktCnt OBJECT-TYPE
			SYNTAX Counter32
			MAX-ACCESS read-only
			STATUS current
			DESCRIPTION
				"ARP inspection invalid same packet counters."
			::= { sleArpInspectInvalidLogEntry 3 }

		
		sleArpInspectInvalidLogOpcode OBJECT-TYPE
			SYNTAX INTEGER
				{
				arpopRequest(1),
				arpopReply(2)
				}
			MAX-ACCESS read-only
			STATUS current
			DESCRIPTION
				"ARP protocol opcodes."
			::= { sleArpInspectInvalidLogEntry 4 }

		
		sleArpInspectInvalidLogPortNumber OBJECT-TYPE
			SYNTAX INTEGER
			MAX-ACCESS read-only
			STATUS current
			DESCRIPTION
				"ARP inspection invalid port number."
			::= { sleArpInspectInvalidLogEntry 5 }

		
		sleArpInspectInvalidLogVlanId OBJECT-TYPE
			SYNTAX INTEGER
			MAX-ACCESS read-only
			STATUS current
			DESCRIPTION
				"ARP inspection invalid vlan id."
			::= { sleArpInspectInvalidLogEntry 6 }

		
		sleArpInspectInvalidLogSrcMacAddr OBJECT-TYPE
			SYNTAX OCTET STRING (SIZE (0..6))
			MAX-ACCESS read-only
			STATUS current
			DESCRIPTION
				"ARP inspection invalid source mac address."
			::= { sleArpInspectInvalidLogEntry 7 }

		
		sleArpInspectInvalidLogSrcIpAddr OBJECT-TYPE
			SYNTAX IpAddress
			MAX-ACCESS read-only
			STATUS current
			DESCRIPTION
				"ARP inspection invalid source IP address."
			::= { sleArpInspectInvalidLogEntry 8 }

		
		sleArpInspectInvalidLogDstMacAddr OBJECT-TYPE
			SYNTAX OCTET STRING (SIZE (0..6))
			MAX-ACCESS read-only
			STATUS current
			DESCRIPTION
				"ARP inspection invalid destination mac address."
			::= { sleArpInspectInvalidLogEntry 9 }

		
		sleArpInspectInvalidLogDstIpAddr OBJECT-TYPE
			SYNTAX IpAddress
			MAX-ACCESS read-only
			STATUS current
			DESCRIPTION
				"ARP inspection invalid destination IP address."
			::= { sleArpInspectInvalidLogEntry 10 }

		
		sleArpInspectInvalidLogLastRecvTime OBJECT-TYPE
			SYNTAX OCTET STRING
			MAX-ACCESS read-only
			STATUS current
			DESCRIPTION
				"ARP inspection invalid packet last received time."
			::= { sleArpInspectInvalidLogEntry 11 }

		
		sleSecurityAttack OBJECT IDENTIFIER ::= { sleSecurity 9 }

		
		sleSecurityAttackBasic OBJECT IDENTIFIER ::= { sleSecurityAttack 1 }

		
		sleSecurityAttackBasicBase OBJECT IDENTIFIER ::= { sleSecurityAttackBasic 1 }

		
		sleSecurityAttackBasicBaseInfo OBJECT IDENTIFIER ::= { sleSecurityAttackBasicBase 1 }

		
		sleSecurityAttackBasicBaseInfoGlobalStatus OBJECT-TYPE
			SYNTAX INTEGER
				{
				disable(0),
				enable(1)
				}
			MAX-ACCESS read-only
			STATUS current
			DESCRIPTION
				"The port attack global status."
			::= { sleSecurityAttackBasicBaseInfo 1 }

		
		sleSecurityAttackBasicBaseDosStatus OBJECT-TYPE
			SYNTAX INTEGER
				{
				disable(0),
				enable(1)
				}
			MAX-ACCESS read-only
			STATUS current
			DESCRIPTION
				"The DOS status."
			::= { sleSecurityAttackBasicBaseInfo 2 }

		
		sleSecurityAttackBasicBaseScanStatus OBJECT-TYPE
			SYNTAX INTEGER
				{
				disable(0),
				enable(1)
				}
			MAX-ACCESS read-only
			STATUS current
			DESCRIPTION
				"The Scan status."
			::= { sleSecurityAttackBasicBaseInfo 3 }

		
		sleSecurityAttackBasicBaseCollectInterval OBJECT-TYPE
			SYNTAX Integer32
			MAX-ACCESS read-only
			STATUS current
			DESCRIPTION
				"The sampling interval"
			::= { sleSecurityAttackBasicBaseInfo 4 }

		
		sleSecurityAttackBasicBaseControl OBJECT IDENTIFIER ::= { sleSecurityAttackBasicBase 2 }

		
		sleSecurityAttackBasicBaseControlRequest OBJECT-TYPE
			SYNTAX INTEGER
				{
				setSecurityAttackGlobalStatus(1),
				setSecurityAttackDosStatus(2),
				setSecurityAttackScanStatus(3),
				setSecurityAttackCollectInterval(4),
				setSecurityAttackAllConfig(5)
				}
			MAX-ACCESS read-write
			STATUS current
			DESCRIPTION
				"Description"
			::= { sleSecurityAttackBasicBaseControl 1 }

		
		sleSecurityAttackBasicBaseControlStatus OBJECT-TYPE
			SYNTAX SleControlStatusType
			MAX-ACCESS read-only
			STATUS current
			DESCRIPTION
				"Description"
			::= { sleSecurityAttackBasicBaseControl 2 }

		
		sleSecurityAttackBasicBaseControlTimer OBJECT-TYPE
			SYNTAX Gauge32
			MAX-ACCESS read-write
			STATUS current
			DESCRIPTION
				"Description"
			::= { sleSecurityAttackBasicBaseControl 3 }

		
		sleSecurityAttackBasicBaseControlTimeStamp OBJECT-TYPE
			SYNTAX TimeTicks
			MAX-ACCESS read-only
			STATUS current
			DESCRIPTION
				"Description"
			::= { sleSecurityAttackBasicBaseControl 4 }

		
		sleSecurityAttackBasicBaseControlReqResult OBJECT-TYPE
			SYNTAX SleControlRequestResultType
			MAX-ACCESS read-only
			STATUS current
			DESCRIPTION
				"Result of the last command."
			::= { sleSecurityAttackBasicBaseControl 5 }

		
		sleSecurityAttackBasicBaseControlGlobalStatus OBJECT-TYPE
			SYNTAX INTEGER
				{
				disable(0),
				enable(1)
				}
			MAX-ACCESS read-write
			STATUS current
			DESCRIPTION
				"The port attack global status."
			::= { sleSecurityAttackBasicBaseControl 6 }

		
		sleSecurityAttackBasicBaseControlDosStatus OBJECT-TYPE
			SYNTAX INTEGER
				{
				disable(0),
				enable(1)
				}
			MAX-ACCESS read-write
			STATUS current
			DESCRIPTION
				"The DOS status."
			::= { sleSecurityAttackBasicBaseControl 7 }

		
		sleSecurityAttackBasicBaseControlScanStatus OBJECT-TYPE
			SYNTAX INTEGER
				{
				disable(0),
				enable(1)
				}
			MAX-ACCESS read-write
			STATUS current
			DESCRIPTION
				"The Scan status."
			::= { sleSecurityAttackBasicBaseControl 8 }

		
		sleSecurityAttackBasicBaseControlCollectInterval OBJECT-TYPE
			SYNTAX Integer32
			MAX-ACCESS read-write
			STATUS current
			DESCRIPTION
				"The sampling interval"
			::= { sleSecurityAttackBasicBaseControl 9 }

		
		sleSecurityAttackBasicBaseNotification OBJECT IDENTIFIER ::= { sleSecurityAttackBasicBase 3 }

		
		sleSecurityAttackBasicBaseGlobalStatusChanged NOTIFICATION-TYPE
			OBJECTS { sleSecurityAttackBasicBaseControlRequest, sleSecurityAttackBasicBaseControlTimeStamp, sleSecurityAttackBasicBaseControlReqResult, sleSecurityAttackBasicBaseControlGlobalStatus }
			STATUS current
			DESCRIPTION 
				"setSecurityAttackGlobalStatus"
			::= { sleSecurityAttackBasicBaseNotification 1 }

		
		sleSecurityAttackBasicBaseDosStatusChanged NOTIFICATION-TYPE
			OBJECTS { sleSecurityAttackBasicBaseControlRequest, sleSecurityAttackBasicBaseControlTimeStamp, sleSecurityAttackBasicBaseControlReqResult, sleSecurityAttackBasicBaseControlDosStatus }
			STATUS current
			DESCRIPTION 
				"setSecurityAttackDosStatus"
			::= { sleSecurityAttackBasicBaseNotification 2 }

		
		sleSecurityAttackBasicBaseScanStatusChanged NOTIFICATION-TYPE
			OBJECTS { sleSecurityAttackBasicBaseControlRequest, sleSecurityAttackBasicBaseControlTimeStamp, sleSecurityAttackBasicBaseControlReqResult, sleSecurityAttackBasicBaseControlScanStatus }
			STATUS current
			DESCRIPTION 
				"setSecurityAttackScanStatus"
			::= { sleSecurityAttackBasicBaseNotification 3 }

		
		sleSecurityAttackBasicBaseCollectIntervalChanged NOTIFICATION-TYPE
			OBJECTS { sleSecurityAttackBasicBaseControlRequest, sleSecurityAttackBasicBaseControlTimeStamp, sleSecurityAttackBasicBaseControlReqResult, sleSecurityAttackBasicBaseControlCollectInterval }
			STATUS current
			DESCRIPTION 
				"setSecurityAttackCollectInterval"
			::= { sleSecurityAttackBasicBaseNotification 4 }

		
		sleSecurityAttackBasicBaseAllConfigChanged NOTIFICATION-TYPE
			OBJECTS { sleSecurityAttackBasicBaseControlRequest, sleSecurityAttackBasicBaseControlTimeStamp, sleSecurityAttackBasicBaseControlReqResult, sleSecurityAttackBasicBaseControlGlobalStatus, sleSecurityAttackBasicBaseControlDosStatus, 
				sleSecurityAttackBasicBaseControlScanStatus, sleSecurityAttackBasicBaseControlCollectInterval }
			STATUS current
			DESCRIPTION 
				"setSecurityAttackAllConfig"
			::= { sleSecurityAttackBasicBaseNotification 5 }

		
		sleSecurityAttackBasicPolicy OBJECT IDENTIFIER ::= { sleSecurityAttackBasic 2 }

		
		sleSecurityAttackBasicPolicyInfo OBJECT IDENTIFIER ::= { sleSecurityAttackBasicPolicy 1 }

		
		sleSecurityAttackBasicPolicyAttackType OBJECT-TYPE
			SYNTAX BITS
				{
				none(0),
				tcpDosAttack(1),
				udpDosAttack(2),
				icmpDosAttack(3),
				hostScan(4),
				portScan(5)
				}
			MAX-ACCESS read-only
			STATUS current
			DESCRIPTION
				"The port attack type."
			::= { sleSecurityAttackBasicPolicyInfo 1 }

		
		sleSecurityAttackBasicPolicyBlockTime OBJECT-TYPE
			SYNTAX OCTET STRING
			MAX-ACCESS read-only
			STATUS current
			DESCRIPTION
				"The block time of port attack. (10-86400 sec)"
			::= { sleSecurityAttackBasicPolicyInfo 2 }

		
		sleSecurityAttackBasicPolicyThresholdCount OBJECT-TYPE
			SYNTAX OCTET STRING
			MAX-ACCESS read-only
			STATUS current
			DESCRIPTION
				"Description."
			::= { sleSecurityAttackBasicPolicyInfo 3 }

		
		sleSecurityAttackBasicPolicyCollectPorts OBJECT-TYPE
			SYNTAX OCTET STRING
			MAX-ACCESS read-only
			STATUS current
			DESCRIPTION
				"The Collect ports."
			::= { sleSecurityAttackBasicPolicyInfo 4 }

		
		sleSecurityAttackBasicPolicyControl OBJECT IDENTIFIER ::= { sleSecurityAttackBasicPolicy 2 }

		
		sleSecurityAttackBasicPolicyControlRequest OBJECT-TYPE
			SYNTAX INTEGER
				{
				setSecurityAttackBasicPolicyBlockTime(1),
				setSecurityAttackBasicPolicyThresholdCount(2),
				setSecurityAttackBasicPolicyCollectPorts(3),
				setSecurityAttackBasicPolicyAllConfig(4)
				}
			MAX-ACCESS read-write
			STATUS current
			DESCRIPTION
				"Decsription"
			::= { sleSecurityAttackBasicPolicyControl 1 }

		
		sleSecurityAttackBasicPolicyControlStatus OBJECT-TYPE
			SYNTAX SleControlStatusType
			MAX-ACCESS read-only
			STATUS current
			DESCRIPTION
				"Description"
			::= { sleSecurityAttackBasicPolicyControl 2 }

		
		sleSecurityAttackBasicPolicyControlTimer OBJECT-TYPE
			SYNTAX Gauge32
			MAX-ACCESS read-write
			STATUS current
			DESCRIPTION
				"Description"
			::= { sleSecurityAttackBasicPolicyControl 3 }

		
		sleSecurityAttackBasicPolicyControlTimeStamp OBJECT-TYPE
			SYNTAX TimeTicks
			MAX-ACCESS read-only
			STATUS current
			DESCRIPTION
				"Description"
			::= { sleSecurityAttackBasicPolicyControl 4 }

		
		sleSecurityAttackBasicPolicyControlReqResult OBJECT-TYPE
			SYNTAX SleControlRequestResultType
			MAX-ACCESS read-only
			STATUS current
			DESCRIPTION
				"Result of the last command."
			::= { sleSecurityAttackBasicPolicyControl 5 }

		
		sleSecurityAttackBasicPolicyControlAttackType OBJECT-TYPE
			SYNTAX BITS
				{
				none(0),
				tcpDosAttack(1),
				udpDosAttack(2),
				icmpDosAttack(3),
				hostScan(4),
				portScan(5)
				}
			MAX-ACCESS read-write
			STATUS current
			DESCRIPTION
				"The port attack type."
			::= { sleSecurityAttackBasicPolicyControl 6 }

		
		sleSecurityAttackBasicPolicyControlBlockTime OBJECT-TYPE
			SYNTAX OCTET STRING
			MAX-ACCESS read-write
			STATUS current
			DESCRIPTION
				"The block time of port attack. (10-86400 sec)"
			::= { sleSecurityAttackBasicPolicyControl 7 }

		
		sleSecurityAttackBasicPolicyControlThresholdCount OBJECT-TYPE
			SYNTAX OCTET STRING
			MAX-ACCESS read-write
			STATUS current
			DESCRIPTION
				"Description."
			::= { sleSecurityAttackBasicPolicyControl 8 }

		
		sleSecurityAttackBasicPolicyControlCollectPorts OBJECT-TYPE
			SYNTAX OCTET STRING
			MAX-ACCESS read-write
			STATUS current
			DESCRIPTION
				"The Collect ports."
			::= { sleSecurityAttackBasicPolicyControl 9 }

		
		sleSecurityAttackBasicPolicyNotification OBJECT IDENTIFIER ::= { sleSecurityAttackBasicPolicy 3 }

		
		sleSecurityAttackBasicPolicyBlockTimeChanged NOTIFICATION-TYPE
			OBJECTS { sleSecurityAttackBasicPolicyControlRequest, sleSecurityAttackBasicPolicyControlTimeStamp, sleSecurityAttackBasicPolicyControlReqResult, sleSecurityAttackBasicPolicyControlAttackType, sleSecurityAttackBasicPolicyControlBlockTime
				 }
			STATUS current
			DESCRIPTION 
				"setSecurityAttackBasicPolicyBlockTime"
			::= { sleSecurityAttackBasicPolicyNotification 1 }

		
		sleSecurityAttackBasicPolicyThresholdCountChanged NOTIFICATION-TYPE
			OBJECTS { sleSecurityAttackBasicPolicyControlRequest, sleSecurityAttackBasicPolicyControlTimeStamp, sleSecurityAttackBasicPolicyControlReqResult, sleSecurityAttackBasicPolicyControlAttackType, sleSecurityAttackBasicPolicyControlThresholdCount
				 }
			STATUS current
			DESCRIPTION 
				"setSecurityAttackBasicPolicyThresholdCount"
			::= { sleSecurityAttackBasicPolicyNotification 2 }

		
		sleSecurityAttackBasicPolicyCollectPortsChanged NOTIFICATION-TYPE
			OBJECTS { sleSecurityAttackBasicPolicyControlRequest, sleSecurityAttackBasicPolicyControlTimeStamp, sleSecurityAttackBasicPolicyControlReqResult, sleSecurityAttackBasicPolicyControlCollectPorts }
			STATUS current
			DESCRIPTION 
				"setSecurityAttackBasicPolicyCollectPorts"
			::= { sleSecurityAttackBasicPolicyNotification 3 }

		
		setSecurityAttackBasicPolicyAllConfigChanged NOTIFICATION-TYPE
			OBJECTS { sleSecurityAttackBasicPolicyControlRequest, sleSecurityAttackBasicPolicyControlTimeStamp, sleSecurityAttackBasicPolicyControlReqResult, sleSecurityAttackBasicPolicyControlAttackType, sleSecurityAttackBasicPolicyControlBlockTime, 
				sleSecurityAttackBasicPolicyControlThresholdCount, sleSecurityAttackBasicPolicyControlCollectPorts }
			STATUS current
			DESCRIPTION 
				"Description."
			::= { sleSecurityAttackBasicPolicyNotification 4 }

		
		sleSecurityAttackBasicExceptList OBJECT IDENTIFIER ::= { sleSecurityAttackBasic 3 }

		
		sleSecurityAttackBasicExceptListTable OBJECT-TYPE
			SYNTAX SEQUENCE OF SleSecurityAttackBasicExceptListEntry
			MAX-ACCESS not-accessible
			STATUS current
			DESCRIPTION
				"Description."
			::= { sleSecurityAttackBasicExceptList 1 }

		
		sleSecurityAttackBasicExceptListEntry OBJECT-TYPE
			SYNTAX SleSecurityAttackBasicExceptListEntry
			MAX-ACCESS not-accessible
			STATUS current
			DESCRIPTION
				"Description."
			INDEX { sleSecurityAttackBasicExceptListIndex }
			::= { sleSecurityAttackBasicExceptListTable 1 }

		
		SleSecurityAttackBasicExceptListEntry ::=
			SEQUENCE { 
				sleSecurityAttackBasicExceptListIndex
					Integer32,
				sleSecurityAttackBasicExceptListProtocolType
					INTEGER,
				sleSecurityAttackBasicExceptListSourceIpAddress
					IpAddress,
				sleSecurityAttackBasicExceptListDestinationIpAddress
					IpAddress,
				sleSecurityAttackBasicExceptListIngressPort
					Integer32
			 }

		sleSecurityAttackBasicExceptListIndex OBJECT-TYPE
			SYNTAX Integer32 (1..65535)
			MAX-ACCESS read-only
			STATUS current
			DESCRIPTION
				"The Rule index."
			::= { sleSecurityAttackBasicExceptListEntry 1 }

		
		sleSecurityAttackBasicExceptListProtocolType OBJECT-TYPE
			SYNTAX INTEGER
				{
				any(0),
				tcp(1),
				udp(2),
				icmp(3)
				}
			MAX-ACCESS read-only
			STATUS current
			DESCRIPTION
				"The protocol type"
			::= { sleSecurityAttackBasicExceptListEntry 2 }

		
		sleSecurityAttackBasicExceptListSourceIpAddress OBJECT-TYPE
			SYNTAX IpAddress
			MAX-ACCESS read-only
			STATUS current
			DESCRIPTION
				"The source IP address "
			::= { sleSecurityAttackBasicExceptListEntry 3 }

		
		sleSecurityAttackBasicExceptListDestinationIpAddress OBJECT-TYPE
			SYNTAX IpAddress
			MAX-ACCESS read-only
			STATUS current
			DESCRIPTION
				"The destination IP address "
			::= { sleSecurityAttackBasicExceptListEntry 4 }

		
		sleSecurityAttackBasicExceptListIngressPort OBJECT-TYPE
			SYNTAX Integer32 (1..65535)
			MAX-ACCESS read-only
			STATUS current
			DESCRIPTION
				"The ingress port"
			::= { sleSecurityAttackBasicExceptListEntry 5 }

		
		sleSecurityAttackBasicExceptListControl OBJECT IDENTIFIER ::= { sleSecurityAttackBasicExceptList 2 }

		
		sleSecurityAttackBasicExceptListControlRequest OBJECT-TYPE
			SYNTAX INTEGER
				{
				createSecurityAttackBasicExceptList(1),
				modifySecurityAttackBasicExceptList(2),
				delSecurityAttackBasicExceptList(3)
				}
			MAX-ACCESS read-write
			STATUS current
			DESCRIPTION
				"Description"
			::= { sleSecurityAttackBasicExceptListControl 1 }

		
		sleSecurityAttackBasicExceptListControlStatus OBJECT-TYPE
			SYNTAX SleControlStatusType
			MAX-ACCESS read-only
			STATUS current
			DESCRIPTION
				"Description"
			::= { sleSecurityAttackBasicExceptListControl 2 }

		
		sleSecurityAttackBasicExceptListControlTimer OBJECT-TYPE
			SYNTAX Gauge32
			MAX-ACCESS read-write
			STATUS current
			DESCRIPTION
				"Description"
			::= { sleSecurityAttackBasicExceptListControl 3 }

		
		sleSecurityAttackBasicExceptListControlTimeStamp OBJECT-TYPE
			SYNTAX TimeTicks
			MAX-ACCESS read-only
			STATUS current
			DESCRIPTION
				"Description"
			::= { sleSecurityAttackBasicExceptListControl 4 }

		
		sleSecurityAttackBasicExceptListControlReqResult OBJECT-TYPE
			SYNTAX SleControlRequestResultType
			MAX-ACCESS read-only
			STATUS current
			DESCRIPTION
				"Result of the last command."
			::= { sleSecurityAttackBasicExceptListControl 5 }

		
		sleSecurityAttackBasicExceptListControlRuleIndex OBJECT-TYPE
			SYNTAX Integer32
			MAX-ACCESS read-write
			STATUS current
			DESCRIPTION
				"The rule index of except list. It's specific nuber per each rule."
			::= { sleSecurityAttackBasicExceptListControl 6 }

		
		sleSecurityAttackBasicExceptListControlProtocolType OBJECT-TYPE
			SYNTAX INTEGER
				{
				any(0),
				tcp(1),
				udp(2),
				icmp(3)
				}
			MAX-ACCESS read-write
			STATUS current
			DESCRIPTION
				"The port attack block time (default:300 sec)"
			::= { sleSecurityAttackBasicExceptListControl 7 }

		
		sleSecurityAttackBasicExceptListControlSourceIpAddress OBJECT-TYPE
			SYNTAX IpAddress
			MAX-ACCESS read-write
			STATUS current
			DESCRIPTION
				"Description."
			::= { sleSecurityAttackBasicExceptListControl 8 }

		
		sleSecurityAttackBasicExceptListControlDestinationIpAddress OBJECT-TYPE
			SYNTAX IpAddress
			MAX-ACCESS read-write
			STATUS current
			DESCRIPTION
				"Description."
			::= { sleSecurityAttackBasicExceptListControl 9 }

		
		sleSecurityAttackBasicExceptListControlIngressPort OBJECT-TYPE
			SYNTAX Integer32
			MAX-ACCESS read-write
			STATUS current
			DESCRIPTION
				"The ingress port"
			::= { sleSecurityAttackBasicExceptListControl 10 }

		
		sleSecurityAttackBasicExceptListNotification OBJECT IDENTIFIER ::= { sleSecurityAttackBasicExceptList 3 }

		
		sleSecurityAttackBasicExceptListCreated NOTIFICATION-TYPE
			OBJECTS { sleSecurityAttackBasicExceptListControlRequest, sleSecurityAttackBasicExceptListControlTimeStamp, sleSecurityAttackBasicExceptListControlReqResult, sleSecurityAttackBasicExceptListControlProtocolType, sleSecurityAttackBasicExceptListControlSourceIpAddress, 
				sleSecurityAttackBasicExceptListControlDestinationIpAddress, sleSecurityAttackBasicExceptListControlIngressPort }
			STATUS current
			DESCRIPTION 
				"createSecurityAttackBasicExceptList"
			::= { sleSecurityAttackBasicExceptListNotification 1 }

		
		sleSecurityAttackBasicExceptListChanged NOTIFICATION-TYPE
			OBJECTS { sleSecurityAttackBasicExceptListControlRequest, sleSecurityAttackBasicExceptListControlTimeStamp, sleSecurityAttackBasicExceptListControlReqResult, sleSecurityAttackBasicExceptListControlRuleIndex, sleSecurityAttackBasicExceptListControlProtocolType, 
				sleSecurityAttackBasicExceptListControlSourceIpAddress, sleSecurityAttackBasicExceptListControlDestinationIpAddress, sleSecurityAttackBasicExceptListControlIngressPort }
			STATUS current
			DESCRIPTION 
				"modifySecurityAttackBasicExceptList"
			::= { sleSecurityAttackBasicExceptListNotification 2 }

		
		sleSecurityAttackBasicExceptListDeleted NOTIFICATION-TYPE
			OBJECTS { sleSecurityAttackBasicExceptListControlRequest, sleSecurityAttackBasicExceptListControlTimeStamp, sleSecurityAttackBasicExceptListControlReqResult, sleSecurityAttackBasicExceptListControlRuleIndex }
			STATUS current
			DESCRIPTION 
				"delSecurityAttackBasicExceptList"
			::= { sleSecurityAttackBasicExceptListNotification 3 }

		
		sleSecurityAttackBasicBlackList OBJECT IDENTIFIER ::= { sleSecurityAttackBasic 4 }

		
		sleSecurityAttackBasicBlackListTable OBJECT-TYPE
			SYNTAX SEQUENCE OF SleSecurityAttackBasicBlackListEntry
			MAX-ACCESS not-accessible
			STATUS current
			DESCRIPTION
				"Description."
			::= { sleSecurityAttackBasicBlackList 1 }

		
		sleSecurityAttackBasicBlackListEntry OBJECT-TYPE
			SYNTAX SleSecurityAttackBasicBlackListEntry
			MAX-ACCESS not-accessible
			STATUS current
			DESCRIPTION
				"Description."
			INDEX { sleSecurityAttackBasicExceptListIndex }
			::= { sleSecurityAttackBasicBlackListTable 1 }

		
		SleSecurityAttackBasicBlackListEntry ::=
			SEQUENCE { 
				sleSecurityAttackBasicBlackListIndex
					Integer32,
				sleSecurityAttackBasicBlackListProtocolType
					INTEGER,
				sleSecurityAttackBasicBlackListSourceIpAddress
					IpAddress,
				sleSecurityAttackBasicBlackListDestinationIpAddress
					IpAddress,
				sleSecurityAttackBasicBlackListBlockingStatus
					INTEGER,
				sleSecurityAttackBasicBlackListIgressPort
					Integer32
			 }

		sleSecurityAttackBasicBlackListIndex OBJECT-TYPE
			SYNTAX Integer32 (1..65535)
			MAX-ACCESS read-only
			STATUS current
			DESCRIPTION
				"The Rule index."
			::= { sleSecurityAttackBasicBlackListEntry 1 }

		
		sleSecurityAttackBasicBlackListProtocolType OBJECT-TYPE
			SYNTAX INTEGER
				{
				any(0),
				tcp(1),
				udp(2),
				icmp(3)
				}
			MAX-ACCESS read-only
			STATUS current
			DESCRIPTION
				"The protocol type"
			::= { sleSecurityAttackBasicBlackListEntry 2 }

		
		sleSecurityAttackBasicBlackListSourceIpAddress OBJECT-TYPE
			SYNTAX IpAddress
			MAX-ACCESS read-only
			STATUS current
			DESCRIPTION
				"The source IP address "
			::= { sleSecurityAttackBasicBlackListEntry 3 }

		
		sleSecurityAttackBasicBlackListDestinationIpAddress OBJECT-TYPE
			SYNTAX IpAddress
			MAX-ACCESS read-only
			STATUS current
			DESCRIPTION
				"The destination IP address "
			::= { sleSecurityAttackBasicBlackListEntry 4 }

		
		sleSecurityAttackBasicBlackListBlockingStatus OBJECT-TYPE
			SYNTAX INTEGER
				{
				disable(0),
				enable(1)
				}
			MAX-ACCESS read-only
			STATUS current
			DESCRIPTION
				"The blocking status."
			::= { sleSecurityAttackBasicBlackListEntry 5 }

		
		sleSecurityAttackBasicBlackListIgressPort OBJECT-TYPE
			SYNTAX Integer32
			MAX-ACCESS read-only
			STATUS current
			DESCRIPTION
				"The engress port
				"
			::= { sleSecurityAttackBasicBlackListEntry 6 }

		
		sleSecurityAttackBasicBlackListControl OBJECT IDENTIFIER ::= { sleSecurityAttackBasicBlackList 2 }

		
		sleSecurityAttackBasicBlackListControlRequest OBJECT-TYPE
			SYNTAX INTEGER
				{
				createSecurityAttackBasicBlackList(1),
				delSecurityAttackBasicBlackList(2)
				}
			MAX-ACCESS read-write
			STATUS current
			DESCRIPTION
				"Description"
			::= { sleSecurityAttackBasicBlackListControl 1 }

		
		sleSecurityAttackBasicBlackListControlStatus OBJECT-TYPE
			SYNTAX SleControlStatusType
			MAX-ACCESS read-only
			STATUS current
			DESCRIPTION
				"Description"
			::= { sleSecurityAttackBasicBlackListControl 2 }

		
		sleSecurityAttackBasicBlackListControlTimer OBJECT-TYPE
			SYNTAX Gauge32
			MAX-ACCESS read-write
			STATUS current
			DESCRIPTION
				"Description"
			::= { sleSecurityAttackBasicBlackListControl 3 }

		
		sleSecurityAttackBasicBlackListControlTimeStamp OBJECT-TYPE
			SYNTAX TimeTicks
			MAX-ACCESS read-only
			STATUS current
			DESCRIPTION
				"Description"
			::= { sleSecurityAttackBasicBlackListControl 4 }

		
		sleSecurityAttackBasicBlackListControlReqResult OBJECT-TYPE
			SYNTAX SleControlRequestResultType
			MAX-ACCESS read-only
			STATUS current
			DESCRIPTION
				"Result of the last command."
			::= { sleSecurityAttackBasicBlackListControl 5 }

		
		sleSecurityAttackBasicBlackListControlRuleIndex OBJECT-TYPE
			SYNTAX Integer32
			MAX-ACCESS read-write
			STATUS current
			DESCRIPTION
				"The rule index of except list. It's specific nuber per each rule."
			::= { sleSecurityAttackBasicBlackListControl 6 }

		
		sleSecurityAttackBasicBlackListControlProtocolType OBJECT-TYPE
			SYNTAX INTEGER
				{
				any(0),
				tcp(1),
				udp(2),
				icmp(3)
				}
			MAX-ACCESS read-write
			STATUS current
			DESCRIPTION
				"The port attack block time (default:300 sec)"
			::= { sleSecurityAttackBasicBlackListControl 7 }

		
		sleSecurityAttackBasicBlackListControlSourceIpAddress OBJECT-TYPE
			SYNTAX IpAddress
			MAX-ACCESS read-write
			STATUS current
			DESCRIPTION
				"Description."
			::= { sleSecurityAttackBasicBlackListControl 8 }

		
		sleSecurityAttackBasicBlackListControlDestinationIpAddress OBJECT-TYPE
			SYNTAX IpAddress
			MAX-ACCESS read-write
			STATUS current
			DESCRIPTION
				"Description."
			::= { sleSecurityAttackBasicBlackListControl 9 }

		
		sleSecurityAttackBasicBlackListControlIngressPort OBJECT-TYPE
			SYNTAX Integer32
			MAX-ACCESS read-write
			STATUS current
			DESCRIPTION
				"The engress port"
			::= { sleSecurityAttackBasicBlackListControl 10 }

		
		sleSecurityAttackBasicBlackListNotification OBJECT IDENTIFIER ::= { sleSecurityAttackBasicBlackList 3 }

		
		sleSecurityAttackBasicBlackListCreated NOTIFICATION-TYPE
			OBJECTS { sleSecurityAttackBasicBlackListControlRequest, sleSecurityAttackBasicBlackListControlTimeStamp, sleSecurityAttackBasicBlackListControlReqResult, sleSecurityAttackBasicBlackListControlRuleIndex, sleSecurityAttackBasicBlackListControlProtocolType, 
				sleSecurityAttackBasicBlackListControlSourceIpAddress, sleSecurityAttackBasicBlackListControlDestinationIpAddress, sleSecurityAttackBasicBlackListControlIngressPort }
			STATUS current
			DESCRIPTION 
				"createSecurityAttackBasicBlackList"
			::= { sleSecurityAttackBasicBlackListNotification 1 }

		
		sleSecurityAttackBasicBlackListDeleted NOTIFICATION-TYPE
			OBJECTS { sleSecurityAttackBasicBlackListControlRequest, sleSecurityAttackBasicBlackListControlTimeStamp, sleSecurityAttackBasicBlackListControlReqResult, sleSecurityAttackBasicBlackListControlRuleIndex }
			STATUS current
			DESCRIPTION 
				"setSecurityAttackBasicBlackList"
			::= { sleSecurityAttackBasicBlackListNotification 2 }

		
		sleSecurityAttackBasicBlockedList OBJECT IDENTIFIER ::= { sleSecurityAttackBasic 5 }

		
		sleSecurityAttackBasicBlockedListTable OBJECT-TYPE
			SYNTAX SEQUENCE OF SleSecurityAttackBasicBlockedListEntry
			MAX-ACCESS not-accessible
			STATUS current
			DESCRIPTION
				"Description."
			::= { sleSecurityAttackBasicBlockedList 1 }

		
		sleSecurityAttackBasicBlockedListEntry OBJECT-TYPE
			SYNTAX SleSecurityAttackBasicBlockedListEntry
			MAX-ACCESS not-accessible
			STATUS current
			DESCRIPTION
				"Description."
			INDEX { sleSecurityAttackBasicBlockedListIndex }
			::= { sleSecurityAttackBasicBlockedListTable 1 }

		
		SleSecurityAttackBasicBlockedListEntry ::=
			SEQUENCE { 
				sleSecurityAttackBasicBlockedListIndex
					Integer32,
				sleSecurityAttackBasicBlockedListAttackType
					INTEGER,
				sleSecurityAttackBasicBlockedListStartTime
					OCTET STRING,
				sleSecurityAttackBasicBlockedListEndTime
					OCTET STRING,
				sleSecurityAttackBasicBlockedListAttackSourceIp
					IpAddress,
				sleSecurityAttackBasicBlockedListAttackDestinationIp
					IpAddress,
				sleSecurityAttackBasicBlockedListProtocol
					INTEGER,
				sleSecurityAttackBasicBlockedListAttackPktCount
					Counter32,
				sleSecurityAttackBasicBlockedListAttackBlockTime
					Integer32,
				sleSecurityAttackBasicBlockedListBlackListIndex
					Integer32,
				sleSecurityAttackBasicBlockedListIgressPort
					Integer32
			 }

		sleSecurityAttackBasicBlockedListIndex OBJECT-TYPE
			SYNTAX Integer32 (1..65535)
			MAX-ACCESS read-only
			STATUS current
			DESCRIPTION
				"The Rule index."
			::= { sleSecurityAttackBasicBlockedListEntry 1 }

		
		sleSecurityAttackBasicBlockedListAttackType OBJECT-TYPE
			SYNTAX INTEGER
				{
				none(0),
				tcpDosAttack(1),
				udpDosAttack(2),
				icmpDosAttack(3),
				hostScan(4),
				portScan(5),
				staticAttack(6)
				}
			MAX-ACCESS read-only
			STATUS current
			DESCRIPTION
				"The port attack type"
			::= { sleSecurityAttackBasicBlockedListEntry 2 }

		
		sleSecurityAttackBasicBlockedListStartTime OBJECT-TYPE
			SYNTAX OCTET STRING
			MAX-ACCESS read-only
			STATUS current
			DESCRIPTION
				"The start time."
			::= { sleSecurityAttackBasicBlockedListEntry 3 }

		
		sleSecurityAttackBasicBlockedListEndTime OBJECT-TYPE
			SYNTAX OCTET STRING
			MAX-ACCESS read-only
			STATUS current
			DESCRIPTION
				"The End Time"
			::= { sleSecurityAttackBasicBlockedListEntry 4 }

		
		sleSecurityAttackBasicBlockedListAttackSourceIp OBJECT-TYPE
			SYNTAX IpAddress
			MAX-ACCESS read-only
			STATUS current
			DESCRIPTION
				"The attack source ip address"
			::= { sleSecurityAttackBasicBlockedListEntry 5 }

		
		sleSecurityAttackBasicBlockedListAttackDestinationIp OBJECT-TYPE
			SYNTAX IpAddress
			MAX-ACCESS read-only
			STATUS current
			DESCRIPTION
				"The attack Destination ip address"
			::= { sleSecurityAttackBasicBlockedListEntry 6 }

		
		sleSecurityAttackBasicBlockedListProtocol OBJECT-TYPE
			SYNTAX INTEGER
				{
				any(0),
				tcp(1),
				udp(2),
				icmp(3),
				arp(4)
				}
			MAX-ACCESS read-only
			STATUS current
			DESCRIPTION
				"The protocol type."
			::= { sleSecurityAttackBasicBlockedListEntry 7 }

		
		sleSecurityAttackBasicBlockedListAttackPktCount OBJECT-TYPE
			SYNTAX Counter32
			MAX-ACCESS read-only
			STATUS current
			DESCRIPTION
				"The attack packet per second."
			::= { sleSecurityAttackBasicBlockedListEntry 8 }

		
		sleSecurityAttackBasicBlockedListAttackBlockTime OBJECT-TYPE
			SYNTAX Integer32 (10..86400)
			MAX-ACCESS read-only
			STATUS current
			DESCRIPTION
				"The attack block time."
			::= { sleSecurityAttackBasicBlockedListEntry 9 }

		
		sleSecurityAttackBasicBlockedListBlackListIndex OBJECT-TYPE
			SYNTAX Integer32
			MAX-ACCESS read-only
			STATUS current
			DESCRIPTION
				"The Black list index."
			::= { sleSecurityAttackBasicBlockedListEntry 10 }

		
		sleSecurityAttackBasicBlockedListIgressPort OBJECT-TYPE
			SYNTAX Integer32
			MAX-ACCESS read-only
			STATUS current
			DESCRIPTION
				"The engress port
				"
			::= { sleSecurityAttackBasicBlockedListEntry 11 }

		
		sleSecurityAttackBasicBlockedListControl OBJECT IDENTIFIER ::= { sleSecurityAttackBasicBlockedList 2 }

		
		sleSecurityAttackBasicBlockedListControlRequest OBJECT-TYPE
			SYNTAX INTEGER
				{
				setSecurityAttackBasicBlockTime(1),
				delSecurityAttackBasicBlockList(2)
				}
			MAX-ACCESS read-write
			STATUS current
			DESCRIPTION
				"Description"
			::= { sleSecurityAttackBasicBlockedListControl 1 }

		
		sleSecurityAttackBasicBlockedListControlStatus OBJECT-TYPE
			SYNTAX SleControlStatusType
			MAX-ACCESS read-only
			STATUS current
			DESCRIPTION
				"Description"
			::= { sleSecurityAttackBasicBlockedListControl 2 }

		
		sleSecurityAttackBasicBlockedListControlTimer OBJECT-TYPE
			SYNTAX Gauge32
			MAX-ACCESS read-write
			STATUS current
			DESCRIPTION
				"Description"
			::= { sleSecurityAttackBasicBlockedListControl 3 }

		
		sleSecurityAttackBasicBlockedListControlTimeStamp OBJECT-TYPE
			SYNTAX TimeTicks
			MAX-ACCESS read-only
			STATUS current
			DESCRIPTION
				"Description"
			::= { sleSecurityAttackBasicBlockedListControl 4 }

		
		sleSecurityAttackBasicBlockedListControlReqResult OBJECT-TYPE
			SYNTAX SleControlRequestResultType
			MAX-ACCESS read-only
			STATUS current
			DESCRIPTION
				"Result of the last command."
			::= { sleSecurityAttackBasicBlockedListControl 5 }

		
		sleSecurityAttackBasicBlockedListControlRuleIndex OBJECT-TYPE
			SYNTAX Integer32
			MAX-ACCESS read-write
			STATUS current
			DESCRIPTION
				"The Rule index of blocked list. It's specific nuber per each rule."
			::= { sleSecurityAttackBasicBlockedListControl 6 }

		
		sleSecurityAttackBasicBlockedListControlBlockTime OBJECT-TYPE
			SYNTAX Integer32 (10..86400)
			MAX-ACCESS read-write
			STATUS current
			DESCRIPTION
				"The port attack block time "
			::= { sleSecurityAttackBasicBlockedListControl 7 }

		
		sleSecurityAttackBasicBlockedListNotification OBJECT IDENTIFIER ::= { sleSecurityAttackBasicBlockedList 3 }

		
		sleSecurityAttackBasicBlockedListBlockTimeChanged NOTIFICATION-TYPE
			OBJECTS { sleSecurityAttackBasicBlockedListControlRequest, sleSecurityAttackBasicBlockedListControlTimeStamp, sleSecurityAttackBasicBlockedListControlReqResult, sleSecurityAttackBasicBlockedListControlRuleIndex, sleSecurityAttackBasicBlockedListControlBlockTime
				 }
			STATUS current
			DESCRIPTION 
				"setSecurityAttackBasicBlockTime"
			::= { sleSecurityAttackBasicBlockedListNotification 1 }

		
		sleSecurityAttackBasicBlockedListDeleted NOTIFICATION-TYPE
			OBJECTS { sleSecurityAttackBasicBlockedListControlRequest, sleSecurityAttackBasicBlockedListControlTimeStamp, sleSecurityAttackBasicBlockedListControlReqResult, sleSecurityAttackBasicBlockedListControlRuleIndex }
			STATUS current
			DESCRIPTION 
				"delSecurityAttackBasicBlockList"
			::= { sleSecurityAttackBasicBlockedListNotification 2 }

		
		sleSecurityAttackExpansion OBJECT IDENTIFIER ::= { sleSecurityAttack 2 }

		
		sleSecurityAttackExpansionBase OBJECT IDENTIFIER ::= { sleSecurityAttackExpansion 1 }

		
		sleSecurityAttackExpansionBaseInfo OBJECT IDENTIFIER ::= { sleSecurityAttackExpansionBase 1 }

		
		sleSecurityAttackExpansionBaseGlobalStatus OBJECT-TYPE
			SYNTAX INTEGER
				{
				disable(0),
				enable(1)
				}
			MAX-ACCESS read-only
			STATUS current
			DESCRIPTION
				"The port attack global status."
			::= { sleSecurityAttackExpansionBaseInfo 1 }

		
		sleSecurityAttackExpansionBaseControl OBJECT IDENTIFIER ::= { sleSecurityAttackExpansionBase 2 }

		
		sleSecurityAttackExpansionBaseControlRequest OBJECT-TYPE
			SYNTAX INTEGER { setSecurityAttackExpansionGlobalStatus(1) }
			MAX-ACCESS read-write
			STATUS current
			DESCRIPTION
				"Description"
			::= { sleSecurityAttackExpansionBaseControl 1 }

		
		sleSecurityAttackExpansionBaseControlStatus OBJECT-TYPE
			SYNTAX SleControlStatusType
			MAX-ACCESS read-only
			STATUS current
			DESCRIPTION
				"Description"
			::= { sleSecurityAttackExpansionBaseControl 2 }

		
		sleSecurityAttackExpansionBaseControlTimer OBJECT-TYPE
			SYNTAX Gauge32
			MAX-ACCESS read-write
			STATUS current
			DESCRIPTION
				"Description"
			::= { sleSecurityAttackExpansionBaseControl 3 }

		
		sleSecurityAttackExpansionBaseControlTimeStamp OBJECT-TYPE
			SYNTAX TimeTicks
			MAX-ACCESS read-only
			STATUS current
			DESCRIPTION
				"Description"
			::= { sleSecurityAttackExpansionBaseControl 4 }

		
		sleSecurityAttackExpansionBaseControlReqResult OBJECT-TYPE
			SYNTAX SleControlRequestResultType
			MAX-ACCESS read-only
			STATUS current
			DESCRIPTION
				"Result of the last command."
			::= { sleSecurityAttackExpansionBaseControl 5 }

		
		sleSecurityAttackExpansionBaseControlGlobalStatus OBJECT-TYPE
			SYNTAX INTEGER
				{
				disable(0),
				enable(1)
				}
			MAX-ACCESS read-write
			STATUS current
			DESCRIPTION
				"The port attack global status."
			::= { sleSecurityAttackExpansionBaseControl 6 }

		
		sleSecurityAttackExpansionBaseNotification OBJECT IDENTIFIER ::= { sleSecurityAttackExpansionBase 3 }

		
		sleSecurityAttackExpansionBaseGlobalStatusChanged NOTIFICATION-TYPE
			OBJECTS { sleSecurityAttackExpansionBaseControlRequest, sleSecurityAttackExpansionBaseControlTimeStamp, sleSecurityAttackExpansionBaseControlReqResult, sleSecurityAttackExpansionBaseControlGlobalStatus }
			STATUS current
			DESCRIPTION 
				"setSecurityAttackExpansionGlobalStatus"
			::= { sleSecurityAttackExpansionBaseNotification 1 }

		
		sleSecurityAttackExpansionPolicy OBJECT IDENTIFIER ::= { sleSecurityAttackExpansion 2 }

		
		sleSecurityAttackExpansionPolicyTable OBJECT-TYPE
			SYNTAX SEQUENCE OF SleSecurityAttackExpansionPolicyEntry
			MAX-ACCESS not-accessible
			STATUS current
			DESCRIPTION
				"Description."
			::= { sleSecurityAttackExpansionPolicy 1 }

		
		sleSecurityAttackExpansionPolicyEntry OBJECT-TYPE
			SYNTAX SleSecurityAttackExpansionPolicyEntry
			MAX-ACCESS not-accessible
			STATUS current
			DESCRIPTION
				"Description."
			INDEX { sleSecurityAttackExpansionPolicyPortIndex }
			::= { sleSecurityAttackExpansionPolicyTable 1 }

		
		SleSecurityAttackExpansionPolicyEntry ::=
			SEQUENCE { 
				sleSecurityAttackExpansionPolicyPortIndex
					Integer32,
				sleSecurityAttackExpansionPolicyStatus
					INTEGER,
				sleSecurityAttackExpansionPolicyAttackType
					BITS,
				sleSecurityAttackExpansionPolicyBlockTime
					OCTET STRING
			 }

		sleSecurityAttackExpansionPolicyPortIndex OBJECT-TYPE
			SYNTAX Integer32 (1..65535)
			MAX-ACCESS read-only
			STATUS current
			DESCRIPTION
				"The Port Index."
			::= { sleSecurityAttackExpansionPolicyEntry 1 }

		
		sleSecurityAttackExpansionPolicyStatus OBJECT-TYPE
			SYNTAX INTEGER
				{
				disable(0),
				enable(1)
				}
			MAX-ACCESS read-write
			STATUS current
			DESCRIPTION
				"The Port attack feature status(This OID is only for GET)."
			::= { sleSecurityAttackExpansionPolicyEntry 2 }

		
		sleSecurityAttackExpansionPolicyAttackType OBJECT-TYPE
			SYNTAX BITS
				{
				none(0),
				tcpDosAttack(1),
				tcpPortFlooding(2),
				tcpHostRandomFlooding(3),
				tcpHostScanning(4),
				ipSppfing(5),
				udpDosAttack(6),
				udpPortFlooding(7),
				udpHostRandomFlooding(8),
				udpHostScanning(9),
				udpIPSppfing(10),
				icmpDosAttack(11),
				icmpIPSppfing(12),
				icmpHostScanning(13),
				arpMacFlooding(14),
				arpSpoofing(15),
				decoySnare(16),
				hostScan(17),
				portScan(18),
				tcpPortScanning(19),
				udpPortScanning(20),
				staticAttack(21)
				}
			MAX-ACCESS read-only
			STATUS current
			DESCRIPTION
				"The policy status of port attack type."
			::= { sleSecurityAttackExpansionPolicyEntry 3 }

		
		sleSecurityAttackExpansionPolicyBlockTime OBJECT-TYPE
			SYNTAX OCTET STRING
			MAX-ACCESS read-only
			STATUS current
			DESCRIPTION
				"The block time of port attack. (10-86400 sec)"
			::= { sleSecurityAttackExpansionPolicyEntry 4 }

		
		sleSecurityAttackExpansionPolicyControl OBJECT IDENTIFIER ::= { sleSecurityAttackExpansionPolicy 2 }

		
		sleSecurityAttackExpansionPolicyControlRequest OBJECT-TYPE
			SYNTAX INTEGER { setSecurityAttackExpansionPolicy(1) }
			MAX-ACCESS read-write
			STATUS current
			DESCRIPTION
				"Description"
			::= { sleSecurityAttackExpansionPolicyControl 1 }

		
		sleSecurityAttackExpansionPolicyControlStatus OBJECT-TYPE
			SYNTAX SleControlStatusType
			MAX-ACCESS read-only
			STATUS current
			DESCRIPTION
				"Description"
			::= { sleSecurityAttackExpansionPolicyControl 2 }

		
		sleSecurityAttackExpansionPolicyControlTimer OBJECT-TYPE
			SYNTAX Gauge32
			MAX-ACCESS read-write
			STATUS current
			DESCRIPTION
				"Description"
			::= { sleSecurityAttackExpansionPolicyControl 3 }

		
		sleSecurityAttackExpansionPolicyControlTimeStamp OBJECT-TYPE
			SYNTAX TimeTicks
			MAX-ACCESS read-only
			STATUS current
			DESCRIPTION
				"Description"
			::= { sleSecurityAttackExpansionPolicyControl 4 }

		
		sleSecurityAttackExpansionPolicyControlReqResult OBJECT-TYPE
			SYNTAX SleControlRequestResultType
			MAX-ACCESS read-only
			STATUS current
			DESCRIPTION
				"Result of the last command."
			::= { sleSecurityAttackExpansionPolicyControl 5 }

		
		sleSecurityAttackExpansionPolicyControlPortIndex OBJECT-TYPE
			SYNTAX Integer32
			MAX-ACCESS read-write
			STATUS current
			DESCRIPTION
				"The port index."
			::= { sleSecurityAttackExpansionPolicyControl 6 }

		
		sleSecurityAttackExpansionPolicyControlAttackType OBJECT-TYPE
			SYNTAX BITS
				{
				none(0),
				tcpDosAttack(1),
				tcpPortFlooding(2),
				tcpHostRandomFlooding(3),
				tcpHostScanning(4),
				ipSppfing(5),
				udpDosAttack(6),
				udpPortFlooding(7),
				udpHostRandomFlooding(8),
				udpHostScanning(9),
				udpIPSppfing(10),
				icmpDosAttack(11),
				icmpIPSppfing(12),
				icmpHostScanning(13),
				arpMacFlooding(14),
				arpSpoofing(15),
				decoySnare(16),
				hostScan(17),
				portScan(18),
				tcpPortScanning(19),
				udpPortScanning(20),
				staticAttack(21)
				}
			MAX-ACCESS read-write
			STATUS current
			DESCRIPTION
				"The port attack type."
			::= { sleSecurityAttackExpansionPolicyControl 7 }

		
		sleSecurityAttackExpansionPolicyControlBlockTime OBJECT-TYPE
			SYNTAX OCTET STRING
			MAX-ACCESS read-write
			STATUS current
			DESCRIPTION
				"The block time of port attack. (10-86400 sec)"
			::= { sleSecurityAttackExpansionPolicyControl 8 }

		
		sleSecurityAttackExpansionPolicyNotification OBJECT IDENTIFIER ::= { sleSecurityAttackExpansionPolicy 3 }

		
		sleSecurityAttackExpansionPolicyChanged NOTIFICATION-TYPE
			OBJECTS { sleSecurityAttackExpansionPolicyControlRequest, sleSecurityAttackExpansionPolicyControlTimeStamp, sleSecurityAttackExpansionPolicyControlReqResult, sleSecurityAttackExpansionPolicyControlPortIndex, sleSecurityAttackExpansionPolicyControlAttackType, 
				sleSecurityAttackExpansionPolicyControlBlockTime }
			STATUS current
			DESCRIPTION 
				"setSecurityAttackExpansionPolicy"
			::= { sleSecurityAttackExpansionPolicyNotification 1 }

		
		sleSecurityAttackExpansionExceptList OBJECT IDENTIFIER ::= { sleSecurityAttackExpansion 3 }

		
		sleSecurityAttackExpansionExceptListTable OBJECT-TYPE
			SYNTAX SEQUENCE OF SleSecurityAttackExpansionExceptListEntry
			MAX-ACCESS not-accessible
			STATUS current
			DESCRIPTION
				"Description."
			::= { sleSecurityAttackExpansionExceptList 1 }

		
		sleSecurityAttackExpansionExceptListEntry OBJECT-TYPE
			SYNTAX SleSecurityAttackExpansionExceptListEntry
			MAX-ACCESS not-accessible
			STATUS current
			DESCRIPTION
				"Description."
			INDEX { sleSecurityAttackExpansionExceptListPortIndex, sleSecurityAttackExpansionExceptListIndex }
			::= { sleSecurityAttackExpansionExceptListTable 1 }

		
		SleSecurityAttackExpansionExceptListEntry ::=
			SEQUENCE { 
				sleSecurityAttackExpansionExceptListPortIndex
					Integer32,
				sleSecurityAttackExpansionExceptListIndex
					Integer32,
				sleSecurityAttackExpansionExceptListRuleIndex
					Integer32,
				sleSecurityAttackExpansionExceptListProtocolType
					INTEGER,
				sleSecurityAttackExpansionExceptListSourceType
					INTEGER,
				sleSecurityAttackExpansionExceptListSourceIpAddress
					IpAddress,
				sleSecurityAttackExpansionExceptListSourceIpMask
					Integer32,
				sleSecurityAttackExpansionExceptListSourceMac
					OCTET STRING,
				sleSecurityAttackExpansionExceptListSourcePortType
					INTEGER,
				sleSecurityAttackExpansionExceptListSourcePortFrom
					Integer32,
				sleSecurityAttackExpansionExceptListSourcePortTo
					Integer32,
				sleSecurityAttackExpansionExceptListDestinationType
					INTEGER,
				sleSecurityAttackExpansionExceptListDestinationIpAddress
					IpAddress,
				sleSecurityAttackExpansionExceptListDestinationIpMask
					Integer32,
				sleSecurityAttackExpansionExceptListDestinationMac
					OCTET STRING,
				sleSecurityAttackExpansionExceptListDestinationPortType
					INTEGER,
				sleSecurityAttackExpansionExceptListDestinationPortFrom
					Integer32,
				sleSecurityAttackExpansionExceptListDestinationPortTo
					Integer32
			 }

		sleSecurityAttackExpansionExceptListPortIndex OBJECT-TYPE
			SYNTAX Integer32 (1..65535)
			MAX-ACCESS read-only
			STATUS current
			DESCRIPTION
				"The port index."
			::= { sleSecurityAttackExpansionExceptListEntry 1 }

		
		sleSecurityAttackExpansionExceptListIndex OBJECT-TYPE
			SYNTAX Integer32 (1..65535)
			MAX-ACCESS read-only
			STATUS current
			DESCRIPTION
				"The except list index."
			::= { sleSecurityAttackExpansionExceptListEntry 2 }

		
		sleSecurityAttackExpansionExceptListRuleIndex OBJECT-TYPE
			SYNTAX Integer32
			MAX-ACCESS read-only
			STATUS current
			DESCRIPTION
				"The rule index. It's specific nuber per each rule."
			::= { sleSecurityAttackExpansionExceptListEntry 3 }

		
		sleSecurityAttackExpansionExceptListProtocolType OBJECT-TYPE
			SYNTAX INTEGER
				{
				any(0),
				tcp(1),
				udp(2),
				icmp(3),
				arp(4)
				}
			MAX-ACCESS read-only
			STATUS current
			DESCRIPTION
				"The protocol type"
			::= { sleSecurityAttackExpansionExceptListEntry 4 }

		
		sleSecurityAttackExpansionExceptListSourceType OBJECT-TYPE
			SYNTAX INTEGER
				{
				any(0),
				ip(1),
				mac(2)
				}
			MAX-ACCESS read-only
			STATUS current
			DESCRIPTION
				"The Source Type."
			::= { sleSecurityAttackExpansionExceptListEntry 5 }

		
		sleSecurityAttackExpansionExceptListSourceIpAddress OBJECT-TYPE
			SYNTAX IpAddress
			MAX-ACCESS read-only
			STATUS current
			DESCRIPTION
				"The source IP address "
			::= { sleSecurityAttackExpansionExceptListEntry 6 }

		
		sleSecurityAttackExpansionExceptListSourceIpMask OBJECT-TYPE
			SYNTAX Integer32
			MAX-ACCESS read-only
			STATUS current
			DESCRIPTION
				"The source IP address mask"
			::= { sleSecurityAttackExpansionExceptListEntry 7 }

		
		sleSecurityAttackExpansionExceptListSourceMac OBJECT-TYPE
			SYNTAX OCTET STRING
			MAX-ACCESS read-only
			STATUS current
			DESCRIPTION
				"The source MAC address."
			::= { sleSecurityAttackExpansionExceptListEntry 8 }

		
		sleSecurityAttackExpansionExceptListSourcePortType OBJECT-TYPE
			SYNTAX INTEGER
				{
				any(0),
				equal(1),
				range(2)
				}
			MAX-ACCESS read-only
			STATUS current
			DESCRIPTION
				"The source port type."
			::= { sleSecurityAttackExpansionExceptListEntry 9 }

		
		sleSecurityAttackExpansionExceptListSourcePortFrom OBJECT-TYPE
			SYNTAX Integer32
			MAX-ACCESS read-only
			STATUS current
			DESCRIPTION
				"SourcePort Type is Any then 0
				Equal then portNo
				Range then From PortNo"
			::= { sleSecurityAttackExpansionExceptListEntry 10 }

		
		sleSecurityAttackExpansionExceptListSourcePortTo OBJECT-TYPE
			SYNTAX Integer32
			MAX-ACCESS read-only
			STATUS current
			DESCRIPTION
				"SourcePort Type is Any then 0
				Equal then portNo
				Range then From PortNo"
			::= { sleSecurityAttackExpansionExceptListEntry 11 }

		
		sleSecurityAttackExpansionExceptListDestinationType OBJECT-TYPE
			SYNTAX INTEGER
				{
				any(0),
				ip(1),
				mac(2)
				}
			MAX-ACCESS read-only
			STATUS current
			DESCRIPTION
				"The destination Type."
			::= { sleSecurityAttackExpansionExceptListEntry 12 }

		
		sleSecurityAttackExpansionExceptListDestinationIpAddress OBJECT-TYPE
			SYNTAX IpAddress
			MAX-ACCESS read-only
			STATUS current
			DESCRIPTION
				"The destination IP address "
			::= { sleSecurityAttackExpansionExceptListEntry 13 }

		
		sleSecurityAttackExpansionExceptListDestinationIpMask OBJECT-TYPE
			SYNTAX Integer32
			MAX-ACCESS read-only
			STATUS current
			DESCRIPTION
				"The destination IP address mask"
			::= { sleSecurityAttackExpansionExceptListEntry 14 }

		
		sleSecurityAttackExpansionExceptListDestinationMac OBJECT-TYPE
			SYNTAX OCTET STRING
			MAX-ACCESS read-only
			STATUS current
			DESCRIPTION
				"The source MAC address."
			::= { sleSecurityAttackExpansionExceptListEntry 15 }

		
		sleSecurityAttackExpansionExceptListDestinationPortType OBJECT-TYPE
			SYNTAX INTEGER
				{
				any(0),
				equal(1),
				range(2)
				}
			MAX-ACCESS read-only
			STATUS current
			DESCRIPTION
				"The destination port type."
			::= { sleSecurityAttackExpansionExceptListEntry 16 }

		
		sleSecurityAttackExpansionExceptListDestinationPortFrom OBJECT-TYPE
			SYNTAX Integer32
			MAX-ACCESS read-only
			STATUS current
			DESCRIPTION
				"Destination Port Type is Any then 0
				Equal then portNo
				Range then From PortNo
				"
			::= { sleSecurityAttackExpansionExceptListEntry 17 }

		
		sleSecurityAttackExpansionExceptListDestinationPortTo OBJECT-TYPE
			SYNTAX Integer32
			MAX-ACCESS read-only
			STATUS current
			DESCRIPTION
				"Destination Port Type is Any then 0
				Equal then portNo
				Range then From PortNo
				"
			::= { sleSecurityAttackExpansionExceptListEntry 18 }

		
		sleSecurityAttackExpansionExceptListControl OBJECT IDENTIFIER ::= { sleSecurityAttackExpansionExceptList 2 }

		
		sleSecurityAttackExpansionExceptListControlRequest OBJECT-TYPE
			SYNTAX INTEGER
				{
				createSecurityAttackExpansionExceptList(1),
				modifyPortAttackExpansionExceptList(2),
				delPortAttackExpansionExceptList(3)
				}
			MAX-ACCESS read-write
			STATUS current
			DESCRIPTION
				"Description"
			::= { sleSecurityAttackExpansionExceptListControl 1 }

		
		sleSecurityAttackExpansionExceptListControlStatus OBJECT-TYPE
			SYNTAX SleControlStatusType
			MAX-ACCESS read-only
			STATUS current
			DESCRIPTION
				"Description"
			::= { sleSecurityAttackExpansionExceptListControl 2 }

		
		sleSecurityAttackExpansionExceptListControlTimer OBJECT-TYPE
			SYNTAX Gauge32
			MAX-ACCESS read-write
			STATUS current
			DESCRIPTION
				"Description"
			::= { sleSecurityAttackExpansionExceptListControl 3 }

		
		sleSecurityAttackExpansionExceptListControlTimeStamp OBJECT-TYPE
			SYNTAX TimeTicks
			MAX-ACCESS read-only
			STATUS current
			DESCRIPTION
				"Description"
			::= { sleSecurityAttackExpansionExceptListControl 4 }

		
		sleSecurityAttackExpansionExceptListControlReqResult OBJECT-TYPE
			SYNTAX SleControlRequestResultType
			MAX-ACCESS read-only
			STATUS current
			DESCRIPTION
				"Result of the last command."
			::= { sleSecurityAttackExpansionExceptListControl 5 }

		
		sleSecurityAttackExpansionExceptListControlPortIndex OBJECT-TYPE
			SYNTAX Integer32
			MAX-ACCESS read-write
			STATUS current
			DESCRIPTION
				"The port index."
			::= { sleSecurityAttackExpansionExceptListControl 6 }

		
		sleSecurityAttackExpansionExceptListControlRuleIndex OBJECT-TYPE
			SYNTAX Integer32
			MAX-ACCESS read-write
			STATUS current
			DESCRIPTION
				"The rule index of except list. It's specific nuber per each rule."
			::= { sleSecurityAttackExpansionExceptListControl 7 }

		
		sleSecurityAttackExpansionExceptListControlProtocolType OBJECT-TYPE
			SYNTAX INTEGER
				{
				any(0),
				tcp(1),
				udp(2),
				icmp(3),
				arp(4)
				}
			MAX-ACCESS read-write
			STATUS current
			DESCRIPTION
				"The port attack block time (default:300 sec)"
			::= { sleSecurityAttackExpansionExceptListControl 8 }

		
		sleSecurityAttackExpansionExceptListControlSourceType OBJECT-TYPE
			SYNTAX INTEGER
				{
				any(0),
				ip(1),
				mac(2)
				}
			MAX-ACCESS read-write
			STATUS current
			DESCRIPTION
				"Description."
			::= { sleSecurityAttackExpansionExceptListControl 9 }

		
		sleSecurityAttackExpansionExceptListControlSourceIpAddress OBJECT-TYPE
			SYNTAX IpAddress
			MAX-ACCESS read-write
			STATUS current
			DESCRIPTION
				"Description."
			::= { sleSecurityAttackExpansionExceptListControl 10 }

		
		sleSecurityAttackExpansionExceptListControlSourceIpMask OBJECT-TYPE
			SYNTAX Integer32
			MAX-ACCESS read-write
			STATUS current
			DESCRIPTION
				"Description."
			::= { sleSecurityAttackExpansionExceptListControl 11 }

		
		sleSecurityAttackExpansionExceptListControlSourceMac OBJECT-TYPE
			SYNTAX OCTET STRING
			MAX-ACCESS read-write
			STATUS current
			DESCRIPTION
				"The source MAC address."
			::= { sleSecurityAttackExpansionExceptListControl 12 }

		
		sleSecurityAttackExpansionExceptListControlSourcePortType OBJECT-TYPE
			SYNTAX INTEGER
				{
				any(0),
				equal(1),
				range(2)
				}
			MAX-ACCESS read-write
			STATUS current
			DESCRIPTION
				"The destination port type."
			::= { sleSecurityAttackExpansionExceptListControl 13 }

		
		sleSecurityAttackExpansionExceptListControlSourcePortFrom OBJECT-TYPE
			SYNTAX Integer32
			MAX-ACCESS read-write
			STATUS current
			DESCRIPTION
				"Src Port Type is Any then 0
				Equal then portNo
				Range then From PortNo"
			::= { sleSecurityAttackExpansionExceptListControl 14 }

		
		sleSecurityAttackExpansionExceptListControlSourcePortTo OBJECT-TYPE
			SYNTAX Integer32
			MAX-ACCESS read-write
			STATUS current
			DESCRIPTION
				"Src Port Type is Any then 0
				Equal then portNo
				Range then From PortNo"
			::= { sleSecurityAttackExpansionExceptListControl 15 }

		
		sleSecurityAttackExpansionExceptListControlDestinationType OBJECT-TYPE
			SYNTAX INTEGER
				{
				any(0),
				ip(1),
				mac(2)
				}
			MAX-ACCESS read-write
			STATUS current
			DESCRIPTION
				"Description."
			::= { sleSecurityAttackExpansionExceptListControl 16 }

		
		sleSecurityAttackExpansionExceptListControlDestinationIpAddress OBJECT-TYPE
			SYNTAX IpAddress
			MAX-ACCESS read-write
			STATUS current
			DESCRIPTION
				"Description."
			::= { sleSecurityAttackExpansionExceptListControl 17 }

		
		sleSecurityAttackExpansionExceptListControlDestinationIpMask OBJECT-TYPE
			SYNTAX Integer32
			MAX-ACCESS read-write
			STATUS current
			DESCRIPTION
				"Description."
			::= { sleSecurityAttackExpansionExceptListControl 18 }

		
		sleSecurityAttackExpansionExceptListControlDestinationMac OBJECT-TYPE
			SYNTAX Integer32
			MAX-ACCESS read-write
			STATUS current
			DESCRIPTION
				"The source MAC address."
			::= { sleSecurityAttackExpansionExceptListControl 19 }

		
		sleSecurityAttackExpansionExceptListControlDestinationPortType OBJECT-TYPE
			SYNTAX INTEGER
				{
				any(0),
				equal(1),
				range(2)
				}
			MAX-ACCESS read-write
			STATUS current
			DESCRIPTION
				"The destination port type."
			::= { sleSecurityAttackExpansionExceptListControl 20 }

		
		sleSecurityAttackExpansionExceptListControlDestinationPortFrom OBJECT-TYPE
			SYNTAX Integer32
			MAX-ACCESS read-write
			STATUS current
			DESCRIPTION
				"Src Port Type is Any then 0
				Equal then portNo
				Range then From PortNo"
			::= { sleSecurityAttackExpansionExceptListControl 21 }

		
		sleSecurityAttackExpansionExceptListControlDestinationPortTo OBJECT-TYPE
			SYNTAX Integer32
			MAX-ACCESS read-write
			STATUS current
			DESCRIPTION
				"Src Port Type is Any then 0
				Equal then portNo
				Range then From PortNo"
			::= { sleSecurityAttackExpansionExceptListControl 22 }

		
		sleSecurityAttackExpansionExceptListNotification OBJECT IDENTIFIER ::= { sleSecurityAttackExpansionExceptList 3 }

		
		sleSecurityAttackExpansionExceptListCreated NOTIFICATION-TYPE
			OBJECTS { sleSecurityAttackExpansionExceptListControlRequest, sleSecurityAttackExpansionExceptListControlTimeStamp, sleSecurityAttackExpansionExceptListControlReqResult, sleSecurityAttackExpansionExceptListControlPortIndex, sleSecurityAttackExpansionExceptListControlProtocolType, 
				sleSecurityAttackExpansionExceptListControlSourceType, sleSecurityAttackExpansionExceptListControlSourceIpAddress, sleSecurityAttackExpansionExceptListControlSourceIpMask, sleSecurityAttackExpansionExceptListControlSourceMac, sleSecurityAttackExpansionExceptListControlSourcePortType, 
				sleSecurityAttackExpansionExceptListControlSourcePortFrom, sleSecurityAttackExpansionExceptListControlSourcePortTo, sleSecurityAttackExpansionExceptListControlDestinationType, sleSecurityAttackExpansionExceptListControlDestinationIpAddress, sleSecurityAttackExpansionExceptListControlDestinationIpMask, 
				sleSecurityAttackExpansionExceptListControlDestinationMac, sleSecurityAttackExpansionExceptListControlDestinationPortType, sleSecurityAttackExpansionExceptListControlDestinationPortFrom, sleSecurityAttackExpansionExceptListControlDestinationPortTo }
			STATUS current
			DESCRIPTION 
				"createPortAttackExpansionExceptList"
			::= { sleSecurityAttackExpansionExceptListNotification 1 }

		
		sleSecurityAttackExpansionExceptListChanged NOTIFICATION-TYPE
			OBJECTS { sleSecurityAttackExpansionExceptListControlRequest, sleSecurityAttackExpansionExceptListControlTimeStamp, sleSecurityAttackExpansionExceptListControlReqResult, sleSecurityAttackExpansionExceptListControlRuleIndex, sleSecurityAttackExpansionExceptListControlProtocolType, 
				sleSecurityAttackExpansionExceptListControlSourceType, sleSecurityAttackExpansionExceptListControlSourceIpAddress, sleSecurityAttackExpansionExceptListControlSourceIpMask, sleSecurityAttackExpansionExceptListControlSourceMac, sleSecurityAttackExpansionExceptListControlSourcePortType, 
				sleSecurityAttackExpansionExceptListControlSourcePortFrom, sleSecurityAttackExpansionExceptListControlSourcePortTo, sleSecurityAttackExpansionExceptListControlDestinationType, sleSecurityAttackExpansionExceptListControlDestinationIpAddress, sleSecurityAttackExpansionExceptListControlDestinationIpMask, 
				sleSecurityAttackExpansionExceptListControlDestinationMac, sleSecurityAttackExpansionExceptListControlDestinationPortType, sleSecurityAttackExpansionExceptListControlDestinationPortFrom, sleSecurityAttackExpansionExceptListControlDestinationPortTo }
			STATUS current
			DESCRIPTION 
				"modifyPortAttackExpansionExceptList"
			::= { sleSecurityAttackExpansionExceptListNotification 2 }

		
		sleSecurityAttackExpansionExceptListDeleted NOTIFICATION-TYPE
			OBJECTS { sleSecurityAttackExpansionExceptListControlRequest, sleSecurityAttackExpansionExceptListControlTimeStamp, sleSecurityAttackExpansionExceptListControlReqResult, sleSecurityAttackExpansionExceptListControlRuleIndex }
			STATUS current
			DESCRIPTION 
				"delPortAttackExpansionExceptList"
			::= { sleSecurityAttackExpansionExceptListNotification 3 }

		
		sleSecurityAttackExpansionBlockedList OBJECT IDENTIFIER ::= { sleSecurityAttackExpansion 4 }

		
		sleSecurityAttackExpansionBlockedListTable OBJECT-TYPE
			SYNTAX SEQUENCE OF SleSecurityAttackExpansionBlockedListEntry
			MAX-ACCESS not-accessible
			STATUS current
			DESCRIPTION
				"Description."
			::= { sleSecurityAttackExpansionBlockedList 1 }

		
		sleSecurityAttackExpansionBlockedListEntry OBJECT-TYPE
			SYNTAX SleSecurityAttackExpansionBlockedListEntry
			MAX-ACCESS not-accessible
			STATUS current
			DESCRIPTION
				"Description."
			INDEX { sleSecurityAttackExpansionBlockedListPortIndex, sleSecurityAttackExpansionBlockedListIndex }
			::= { sleSecurityAttackExpansionBlockedListTable 1 }

		
		SleSecurityAttackExpansionBlockedListEntry ::=
			SEQUENCE { 
				sleSecurityAttackExpansionBlockedListPortIndex
					Integer32,
				sleSecurityAttackExpansionBlockedListIndex
					Integer32,
				sleSecurityAttackExpansionBlockedListRuleIndex
					Integer32,
				sleSecurityAttackExpansionBlockedListAttackType
					INTEGER,
				sleSecurityAttackExpansionBlockedListAttackBlockType
					BITS,
				sleSecurityAttackExpansionBlockedListStartTime
					OCTET STRING,
				sleSecurityAttackExpansionBlockedListEndTime
					OCTET STRING,
				sleSecurityAttackExpansionBlockedListAttackSourceIp
					IpAddress,
				sleSecurityAttackExpansionBlockedListSourceMac
					OCTET STRING,
				sleSecurityAttackExpansionBlockedListAttackDestinationIp
					IpAddress,
				sleSecurityAttackExpansionBlockedListProtocol
					INTEGER,
				sleSecurityAttackExpansionBlockedListSourcePort
					Integer32,
				sleSecurityAttackExpansionBlockedListDestinationPort
					Integer32,
				sleSecurityAttackExpansionBlockedListAttackPktCount
					Counter32,
				sleSecurityAttackExpansionBlockedListAttackBlockTime
					Integer32
			 }

		sleSecurityAttackExpansionBlockedListPortIndex OBJECT-TYPE
			SYNTAX Integer32 (1..65535)
			MAX-ACCESS read-only
			STATUS current
			DESCRIPTION
				"Description."
			::= { sleSecurityAttackExpansionBlockedListEntry 1 }

		
		sleSecurityAttackExpansionBlockedListIndex OBJECT-TYPE
			SYNTAX Integer32 (1..65535)
			MAX-ACCESS read-only
			STATUS current
			DESCRIPTION
				"The blocked list index."
			::= { sleSecurityAttackExpansionBlockedListEntry 2 }

		
		sleSecurityAttackExpansionBlockedListRuleIndex OBJECT-TYPE
			SYNTAX Integer32
			MAX-ACCESS read-only
			STATUS current
			DESCRIPTION
				"The Rule index of blocked list. It's specific nuber per each rule."
			::= { sleSecurityAttackExpansionBlockedListEntry 3 }

		
		sleSecurityAttackExpansionBlockedListAttackType OBJECT-TYPE
			SYNTAX INTEGER
				{
				none(0),
				tcpDosAttack(1),
				tcpPortFlooding(2),
				tcpHostRandomFlooding(3),
				tcpHostScanning(4),
				ipSppfing(5),
				udpDosAttack(6),
				udpPortFlooding(7),
				udpHostRandomFlooding(8),
				udpHostScanning(9),
				udpIPSppfing(10),
				icmpDosAttack(11),
				icmpIPSppfing(12),
				icmpHostScanning(13),
				arpMacFlooding(14),
				arpSpoofing(15),
				decoySnare(16),
				hostScan(17),
				portScan(18),
				tcpPortScanning(19),
				udpPortScanning(20),
				staticAttack(21)
				}
			MAX-ACCESS read-only
			STATUS current
			DESCRIPTION
				"The port attack type"
			::= { sleSecurityAttackExpansionBlockedListEntry 4 }

		
		sleSecurityAttackExpansionBlockedListAttackBlockType OBJECT-TYPE
			SYNTAX BITS
				{
				none(0),
				sourceIp(1),
				sourceMac(2),
				sourcePort(3),
				destinationIp(4),
				destinationPort(5)
				}
			MAX-ACCESS read-only
			STATUS current
			DESCRIPTION
				"The attack block type."
			::= { sleSecurityAttackExpansionBlockedListEntry 5 }

		
		sleSecurityAttackExpansionBlockedListStartTime OBJECT-TYPE
			SYNTAX OCTET STRING
			MAX-ACCESS read-only
			STATUS current
			DESCRIPTION
				"The start time."
			::= { sleSecurityAttackExpansionBlockedListEntry 6 }

		
		sleSecurityAttackExpansionBlockedListEndTime OBJECT-TYPE
			SYNTAX OCTET STRING
			MAX-ACCESS read-only
			STATUS current
			DESCRIPTION
				"The End Time"
			::= { sleSecurityAttackExpansionBlockedListEntry 7 }

		
		sleSecurityAttackExpansionBlockedListAttackSourceIp OBJECT-TYPE
			SYNTAX IpAddress
			MAX-ACCESS read-only
			STATUS current
			DESCRIPTION
				"The attack source ip address"
			::= { sleSecurityAttackExpansionBlockedListEntry 8 }

		
		sleSecurityAttackExpansionBlockedListSourceMac OBJECT-TYPE
			SYNTAX OCTET STRING
			MAX-ACCESS read-only
			STATUS current
			DESCRIPTION
				"The attack source MAC address"
			::= { sleSecurityAttackExpansionBlockedListEntry 9 }

		
		sleSecurityAttackExpansionBlockedListAttackDestinationIp OBJECT-TYPE
			SYNTAX IpAddress
			MAX-ACCESS read-only
			STATUS current
			DESCRIPTION
				"The attack Destination ip address"
			::= { sleSecurityAttackExpansionBlockedListEntry 10 }

		
		sleSecurityAttackExpansionBlockedListProtocol OBJECT-TYPE
			SYNTAX INTEGER
				{
				any(0),
				tcp(1),
				udp(2),
				icmp(3),
				arp(4)
				}
			MAX-ACCESS read-only
			STATUS current
			DESCRIPTION
				"The protocol type."
			::= { sleSecurityAttackExpansionBlockedListEntry 11 }

		
		sleSecurityAttackExpansionBlockedListSourcePort OBJECT-TYPE
			SYNTAX Integer32 (0..65535)
			MAX-ACCESS read-only
			STATUS current
			DESCRIPTION
				"The source port (0: any)"
			::= { sleSecurityAttackExpansionBlockedListEntry 12 }

		
		sleSecurityAttackExpansionBlockedListDestinationPort OBJECT-TYPE
			SYNTAX Integer32 (0..65535)
			MAX-ACCESS read-only
			STATUS current
			DESCRIPTION
				"The destination port (0: any)"
			::= { sleSecurityAttackExpansionBlockedListEntry 13 }

		
		sleSecurityAttackExpansionBlockedListAttackPktCount OBJECT-TYPE
			SYNTAX Counter32
			MAX-ACCESS read-only
			STATUS current
			DESCRIPTION
				"The attack packet per second."
			::= { sleSecurityAttackExpansionBlockedListEntry 14 }

		
		sleSecurityAttackExpansionBlockedListAttackBlockTime OBJECT-TYPE
			SYNTAX Integer32 (-1 | 10..86400)
			MAX-ACCESS read-only
			STATUS current
			DESCRIPTION
				"The attack block time."
			::= { sleSecurityAttackExpansionBlockedListEntry 15 }

		
		sleSecurityAttackExpansionBlockedListControl OBJECT IDENTIFIER ::= { sleSecurityAttackExpansionBlockedList 2 }

		
		sleSecurityAttackExpansionBlockedListControlRequest OBJECT-TYPE
			SYNTAX INTEGER { setPortAttackExpansionBlockTime(1) }
			MAX-ACCESS read-write
			STATUS current
			DESCRIPTION
				"Description"
			::= { sleSecurityAttackExpansionBlockedListControl 1 }

		
		sleSecurityAttackExpansionBlockedListControlStatus OBJECT-TYPE
			SYNTAX SleControlStatusType
			MAX-ACCESS read-only
			STATUS current
			DESCRIPTION
				"Description"
			::= { sleSecurityAttackExpansionBlockedListControl 2 }

		
		sleSecurityAttackExpansionBlockedListControlTimer OBJECT-TYPE
			SYNTAX Gauge32
			MAX-ACCESS read-write
			STATUS current
			DESCRIPTION
				"Description"
			::= { sleSecurityAttackExpansionBlockedListControl 3 }

		
		sleSecurityAttackExpansionBlockedListControlTimeStamp OBJECT-TYPE
			SYNTAX TimeTicks
			MAX-ACCESS read-only
			STATUS current
			DESCRIPTION
				"Description"
			::= { sleSecurityAttackExpansionBlockedListControl 4 }

		
		sleSecurityAttackExpansionBlockedListControlReqResult OBJECT-TYPE
			SYNTAX SleControlRequestResultType
			MAX-ACCESS read-only
			STATUS current
			DESCRIPTION
				"Result of the last command."
			::= { sleSecurityAttackExpansionBlockedListControl 5 }

		
		sleSecurityAttackExpansionBlockedListControlRuleIndex OBJECT-TYPE
			SYNTAX Integer32
			MAX-ACCESS read-write
			STATUS current
			DESCRIPTION
				"The Rule index of blocked list. It's specific nuber per each rule."
			::= { sleSecurityAttackExpansionBlockedListControl 6 }

		
		sleSecurityAttackExpansionBlockedListControlBlockTime OBJECT-TYPE
			SYNTAX Integer32 (-1 | 10..86400)
			MAX-ACCESS read-write
			STATUS current
			DESCRIPTION
				"The port attack block time "
			::= { sleSecurityAttackExpansionBlockedListControl 7 }

		
		sleSecurityAttackExpansionBlockedListNotification OBJECT IDENTIFIER ::= { sleSecurityAttackExpansionBlockedList 3 }

		
		sleSecurityAttackExpansionBlockedListBlockTimeChanged NOTIFICATION-TYPE
			OBJECTS { sleSecurityAttackExpansionBlockedListControlRequest, sleSecurityAttackExpansionBlockedListControlTimeStamp, sleSecurityAttackExpansionBlockedListControlReqResult, sleSecurityAttackExpansionBlockedListControlRuleIndex, sleSecurityAttackExpansionBlockedListControlBlockTime
				 }
			STATUS current
			DESCRIPTION 
				"setPortAttackExpansionBlockTime"
			::= { sleSecurityAttackExpansionBlockedListNotification 1 }

		
		sleNDInspection OBJECT IDENTIFIER ::= { sleSecurity 12 }

		
		sleNDInspectBase OBJECT IDENTIFIER ::= { sleNDInspection 1 }

		
		sleNDInspectBaseInfo OBJECT IDENTIFIER ::= { sleNDInspectBase 1 }

		
		sleNDInspectLogBufferSize OBJECT-TYPE
			SYNTAX Integer32 (0..1024)
			MAX-ACCESS read-only
			STATUS current
			DESCRIPTION
				"Description."
			::= { sleNDInspectBaseInfo 1 }

		
		sleNDInspectLogEntry OBJECT-TYPE
			SYNTAX Integer32 (0..1024)
			MAX-ACCESS read-only
			STATUS current
			DESCRIPTION
				"Description."
			::= { sleNDInspectBaseInfo 2 }

		
		sleNDInspectLogInterval OBJECT-TYPE
			SYNTAX Integer32 (0..86400)
			MAX-ACCESS read-only
			STATUS current
			DESCRIPTION
				"Description."
			::= { sleNDInspectBaseInfo 3 }

		
		sleNDInspectBaseControl OBJECT IDENTIFIER ::= { sleNDInspectBase 2 }

		
		sleNDInspectControlRequest OBJECT-TYPE
			SYNTAX INTEGER
				{
				setNDInspectLogBufferSize(1),
				setNDInspectLogRate(2)
				}
			MAX-ACCESS read-write
			STATUS current
			DESCRIPTION
				"Description"
			::= { sleNDInspectBaseControl 1 }

		
		sleNDInspectControlStatus OBJECT-TYPE
			SYNTAX SleControlStatusType
			MAX-ACCESS read-only
			STATUS current
			DESCRIPTION
				"Description"
			::= { sleNDInspectBaseControl 2 }

		
		sleNDInspectControlTimer OBJECT-TYPE
			SYNTAX Gauge32
			MAX-ACCESS read-write
			STATUS current
			DESCRIPTION
				"Description"
			::= { sleNDInspectBaseControl 3 }

		
		sleNDInspectControlTimeStamp OBJECT-TYPE
			SYNTAX TimeTicks
			MAX-ACCESS read-only
			STATUS current
			DESCRIPTION
				"Description"
			::= { sleNDInspectBaseControl 4 }

		
		sleNDInspectControlReqResult OBJECT-TYPE
			SYNTAX SleControlRequestResultType
			MAX-ACCESS read-only
			STATUS current
			DESCRIPTION
				"Result of the last command."
			::= { sleNDInspectBaseControl 5 }

		
		sleNDInspectControlLogBufferSize OBJECT-TYPE
			SYNTAX Integer32 (0..1024)
			MAX-ACCESS read-write
			STATUS current
			DESCRIPTION
				"Description."
			::= { sleNDInspectBaseControl 6 }

		
		sleNDInspectControlLogEntry OBJECT-TYPE
			SYNTAX Integer32 (0..1024)
			MAX-ACCESS read-write
			STATUS current
			DESCRIPTION
				"Description."
			::= { sleNDInspectBaseControl 7 }

		
		sleNDInspectControlLogInterval OBJECT-TYPE
			SYNTAX Integer32 (0..86400)
			MAX-ACCESS read-write
			STATUS current
			DESCRIPTION
				"Description."
			::= { sleNDInspectBaseControl 8 }

		
		sleNDInspectBaseNotifications OBJECT IDENTIFIER ::= { sleNDInspectBase 3 }

		
		sleNDInspectLogBufferSizeChanged NOTIFICATION-TYPE
			OBJECTS { sleNDInspectControlRequest, sleNDInspectControlTimeStamp, sleNDInspectControlReqResult, sleNDInspectControlLogBufferSize }
			STATUS current
			DESCRIPTION 
				"Description."
			::= { sleNDInspectBaseNotifications 1 }

		
		sleNDInspectLogRateChanged NOTIFICATION-TYPE
			OBJECTS { sleNDInspectControlRequest, sleNDInspectControlTimeStamp, sleNDInspectControlReqResult, sleNDInspectControlLogEntry, sleNDInspectControlLogInterval
				 }
			STATUS current
			DESCRIPTION 
				"Description."
			::= { sleNDInspectBaseNotifications 2 }

		
		sleNDACL OBJECT IDENTIFIER ::= { sleNDInspection 2 }

		
		sleNDAclTable OBJECT-TYPE
			SYNTAX SEQUENCE OF SleNDAclEntry
			MAX-ACCESS not-accessible
			STATUS current
			DESCRIPTION
				"Description."
			::= { sleNDACL 1 }

		
		sleNDAclEntry OBJECT-TYPE
			SYNTAX SleNDAclEntry
			MAX-ACCESS not-accessible
			STATUS current
			DESCRIPTION
				"Description."
			INDEX { sleNDAclIndex }
			::= { sleNDAclTable 1 }

		
		SleNDAclEntry ::=
			SEQUENCE { 
				sleNDAclIndex
					INTEGER,
				sleNDAclName
					OCTET STRING,
				sleNDAclNumEntries
					INTEGER
			 }

		sleNDAclIndex OBJECT-TYPE
			SYNTAX INTEGER (1..2147483647)
			MAX-ACCESS read-only
			STATUS current
			DESCRIPTION
				"Description."
			::= { sleNDAclEntry 1 }

		
		sleNDAclName OBJECT-TYPE
			SYNTAX OCTET STRING (SIZE (1..255))
			MAX-ACCESS read-only
			STATUS current
			DESCRIPTION
				"The name of ND ACL."
			::= { sleNDAclEntry 2 }

		
		sleNDAclNumEntries OBJECT-TYPE
			SYNTAX INTEGER (1..2147483647)
			MAX-ACCESS read-only
			STATUS current
			DESCRIPTION
				"Number of Entries"
			::= { sleNDAclEntry 3 }

		
		sleNDAclControl OBJECT IDENTIFIER ::= { sleNDACL 2 }

		
		sleNDAclControlRequest OBJECT-TYPE
			SYNTAX INTEGER
				{
				createNDAcl(1),
				destroyNDAcl(2)
				}
			MAX-ACCESS read-write
			STATUS current
			DESCRIPTION
				"Description"
			::= { sleNDAclControl 1 }

		
		sleNDAclControlStatus OBJECT-TYPE
			SYNTAX SleControlStatusType
			MAX-ACCESS read-only
			STATUS current
			DESCRIPTION
				"Description"
			::= { sleNDAclControl 2 }

		
		sleNDAclControlTimer OBJECT-TYPE
			SYNTAX Gauge32
			MAX-ACCESS read-write
			STATUS current
			DESCRIPTION
				"Description"
			::= { sleNDAclControl 3 }

		
		sleNDAclControlTimeStamp OBJECT-TYPE
			SYNTAX TimeTicks
			MAX-ACCESS read-only
			STATUS current
			DESCRIPTION
				"Description"
			::= { sleNDAclControl 4 }

		
		sleNDAclControlReqResult OBJECT-TYPE
			SYNTAX SleControlRequestResultType
			MAX-ACCESS read-only
			STATUS current
			DESCRIPTION
				"Result of the last command."
			::= { sleNDAclControl 5 }

		
		sleNDAclControlIndex OBJECT-TYPE
			SYNTAX Integer32
			MAX-ACCESS read-write
			STATUS current
			DESCRIPTION
				"Description."
			::= { sleNDAclControl 6 }

		
		sleNDAclControlName OBJECT-TYPE
			SYNTAX OCTET STRING (SIZE (1..255))
			MAX-ACCESS read-write
			STATUS current
			DESCRIPTION
				"The name of acl."
			::= { sleNDAclControl 7 }

		
		sleNDAclNotifications OBJECT IDENTIFIER ::= { sleNDACL 3 }

		
		sleNDAclCreated NOTIFICATION-TYPE
			OBJECTS { sleNDAclControlRequest, sleNDAclControlTimeStamp, sleNDAclControlReqResult, sleNDAclControlName }
			STATUS current
			DESCRIPTION 
				"sleNDInspectValidateControl"
			::= { sleNDAclNotifications 1 }

		
		sleNDAclDestroyed NOTIFICATION-TYPE
			OBJECTS { sleNDAclControlRequest, sleNDAclControlTimeStamp, sleNDAclControlReqResult, sleNDAclControlIndex }
			STATUS current
			DESCRIPTION 
				"sleNDInspectValidateControl"
			::= { sleNDAclNotifications 2 }

		
		sleNDACLRule OBJECT IDENTIFIER ::= { sleNDInspection 3 }

		
		sleNDAclRuleTable OBJECT-TYPE
			SYNTAX SEQUENCE OF SleNDAclRuleEntry
			MAX-ACCESS not-accessible
			STATUS current
			DESCRIPTION
				"Description."
			::= { sleNDACLRule 1 }

		
		sleNDAclRuleEntry OBJECT-TYPE
			SYNTAX SleNDAclRuleEntry
			MAX-ACCESS not-accessible
			STATUS current
			DESCRIPTION
				"Description."
			INDEX { sleNDAclIndex, sleNDAclRuleIndex }
			::= { sleNDAclRuleTable 1 }

		
		SleNDAclRuleEntry ::=
			SEQUENCE { 
				sleNDAclRuleAclIndex
					INTEGER,
				sleNDAclRuleIndex
					INTEGER,
				sleNDAclRuleAction
					INTEGER,
				sleNDAclRuleType
					INTEGER,
				sleNDAclRuleRangeStartIPv6
					InetAddressIPv6,
				sleNDAclRuleRangeEndIPv6
					InetAddressIPv6,
				sleNDAclRuleIPv6Address
					InetAddressIPv6,
				sleNDAclRuleIPv6Mask
					Integer32,
				sleNDAclRuleMacAddr
					MacAddress,
				sleNDAclRuleMacType
					INTEGER
			 }

		sleNDAclRuleAclIndex OBJECT-TYPE
			SYNTAX INTEGER (0..2147483647)
			MAX-ACCESS read-only
			STATUS current
			DESCRIPTION
				"ACL Index"
			::= { sleNDAclRuleEntry 1 }

		
		sleNDAclRuleIndex OBJECT-TYPE
			SYNTAX INTEGER (0..2147483647)
			MAX-ACCESS read-only
			STATUS current
			DESCRIPTION
				"ACL entry Index"
			::= { sleNDAclRuleEntry 2 }

		
		sleNDAclRuleAction OBJECT-TYPE
			SYNTAX INTEGER
				{
				deny(0),
				permit(1)
				}
			MAX-ACCESS read-only
			STATUS current
			DESCRIPTION
				"The permit/deny control used per entry"
			::= { sleNDAclRuleEntry 3 }

		
		sleNDAclRuleType OBJECT-TYPE
			SYNTAX INTEGER
				{
				subnet(1),
				range(2),
				dhcpv6Snooping(3)
				}
			MAX-ACCESS read-only
			STATUS current
			DESCRIPTION
				"Specify entry type is ipv6 address or ipv6 range or dhcpv6 snooping inspection. 
				dhcpv6 snooping is valid in case of support the dhcpv6 snooping inspection.
				"
			::= { sleNDAclRuleEntry 4 }

		
		sleNDAclRuleRangeStartIPv6 OBJECT-TYPE
			SYNTAX InetAddressIPv6
			MAX-ACCESS read-only
			STATUS current
			DESCRIPTION
				"Valid if sleNDAclRuleType is 1 (range) , Otherwise this value is invalid."
			::= { sleNDAclRuleEntry 5 }

		
		sleNDAclRuleRangeEndIPv6 OBJECT-TYPE
			SYNTAX InetAddressIPv6
			MAX-ACCESS read-only
			STATUS current
			DESCRIPTION
				"Valid if sleNDAclRuleType is 1 (range), 
				Otherwise this value is invalid.
				"
			::= { sleNDAclRuleEntry 6 }

		
		sleNDAclRuleIPv6Address OBJECT-TYPE
			SYNTAX InetAddressIPv6
			MAX-ACCESS read-only
			STATUS current
			DESCRIPTION
				"IPV6Address. Valid if sleNDAclRuleType is 0(subnet)."
			::= { sleNDAclRuleEntry 7 }

		
		sleNDAclRuleIPv6Mask OBJECT-TYPE
			SYNTAX Integer32 (1..128)
			MAX-ACCESS read-only
			STATUS current
			DESCRIPTION
				"SubnetMask. 
				Valid if sleNDAclRuleType is 0(subnet).
				"
			::= { sleNDAclRuleEntry 8 }

		
		sleNDAclRuleMacAddr OBJECT-TYPE
			SYNTAX MacAddress
			MAX-ACCESS read-only
			STATUS current
			DESCRIPTION
				"Mac Address. If sleNDAclRuleMacType is 0(any) ,this value is invalid."
			::= { sleNDAclRuleEntry 9 }

		
		sleNDAclRuleMacType OBJECT-TYPE
			SYNTAX INTEGER
				{
				any(0),
				host(1),
				pattern(2)
				}
			MAX-ACCESS read-only
			STATUS current
			DESCRIPTION
				"Mac Address Type."
			::= { sleNDAclRuleEntry 10 }

		
		sleNDAclRuleControl OBJECT IDENTIFIER ::= { sleNDACLRule 2 }

		
		sleNDAclRuleControlRequest OBJECT-TYPE
			SYNTAX INTEGER
				{
				createNDAclRule(1),
				destroyNDAclRule(2)
				}
			MAX-ACCESS read-write
			STATUS current
			DESCRIPTION
				"Description"
			::= { sleNDAclRuleControl 1 }

		
		sleNDAclRuleControlStatus OBJECT-TYPE
			SYNTAX SleControlStatusType
			MAX-ACCESS read-only
			STATUS current
			DESCRIPTION
				"Description"
			::= { sleNDAclRuleControl 2 }

		
		sleNDAclRuleControlTimer OBJECT-TYPE
			SYNTAX Gauge32
			MAX-ACCESS read-write
			STATUS current
			DESCRIPTION
				"Description"
			::= { sleNDAclRuleControl 3 }

		
		sleNDAclRuleControlTimeStamp OBJECT-TYPE
			SYNTAX TimeTicks
			MAX-ACCESS read-only
			STATUS current
			DESCRIPTION
				"Description"
			::= { sleNDAclRuleControl 4 }

		
		sleNDAclRuleControlReqResult OBJECT-TYPE
			SYNTAX SleControlRequestResultType
			MAX-ACCESS read-only
			STATUS current
			DESCRIPTION
				"Result of the last command."
			::= { sleNDAclRuleControl 5 }

		
		sleNDAclRuleControlAclIndex OBJECT-TYPE
			SYNTAX Integer32
			MAX-ACCESS read-write
			STATUS current
			DESCRIPTION
				"The name of acl."
			::= { sleNDAclRuleControl 6 }

		
		sleNDAclRuleControlIndex OBJECT-TYPE
			SYNTAX Integer32
			MAX-ACCESS read-write
			STATUS current
			DESCRIPTION
				"The entry index within ACL"
			::= { sleNDAclRuleControl 7 }

		
		sleNDAclRuleControlAction OBJECT-TYPE
			SYNTAX INTEGER
				{
				deny(0),
				permit(1)
				}
			MAX-ACCESS read-write
			STATUS current
			DESCRIPTION
				"The permit/deny control used per entry"
			::= { sleNDAclRuleControl 8 }

		
		sleNDAclRuleControlType OBJECT-TYPE
			SYNTAX INTEGER
				{
				subnet(1),
				range(2),
				dhcpSnooping(3)
				}
			MAX-ACCESS read-write
			STATUS current
			DESCRIPTION
				"If type of entry is 1, sleNDAclEntryControlMacType must be 0. 
				dhcpv6Snooping is valid in case of support the dhcpv6 snooping inspection."
			::= { sleNDAclRuleControl 9 }

		
		sleNDAclRuleControlRangeStartIPv6 OBJECT-TYPE
			SYNTAX InetAddressIPv6
			MAX-ACCESS read-write
			STATUS current
			DESCRIPTION
				"Description"
			::= { sleNDAclRuleControl 10 }

		
		sleNDAclRuleControlRangeEndIPv6 OBJECT-TYPE
			SYNTAX InetAddressIPv6
			MAX-ACCESS read-write
			STATUS current
			DESCRIPTION
				"Description"
			::= { sleNDAclRuleControl 11 }

		
		sleNDAclRuleControlIPv6Address OBJECT-TYPE
			SYNTAX InetAddressIPv6
			MAX-ACCESS read-write
			STATUS current
			DESCRIPTION
				"Description"
			::= { sleNDAclRuleControl 12 }

		
		sleNDAclRuleControlIPv6Mask OBJECT-TYPE
			SYNTAX INTEGER (1..128)
			MAX-ACCESS read-write
			STATUS current
			DESCRIPTION
				"Description"
			::= { sleNDAclRuleControl 13 }

		
		sleNDAclRuleControlMacAddr OBJECT-TYPE
			SYNTAX MacAddress
			MAX-ACCESS read-write
			STATUS current
			DESCRIPTION
				"Mac Address. If sleNDAclRuleControlMacType is 0(any) ,this value is invalid."
			::= { sleNDAclRuleControl 14 }

		
		sleNDAclRuleControlMacType OBJECT-TYPE
			SYNTAX INTEGER
				{
				any(0),
				host(1),
				pattern(2)
				}
			MAX-ACCESS read-write
			STATUS current
			DESCRIPTION
				"Description"
			::= { sleNDAclRuleControl 15 }

		
		sleNDAclRuleNotifications OBJECT IDENTIFIER ::= { sleNDACLRule 3 }

		
		sleNDAclRuleCreated NOTIFICATION-TYPE
			OBJECTS { sleNDAclRuleControlRequest, sleNDAclRuleControlTimeStamp, sleNDAclRuleControlReqResult, sleNDAclRuleAction, sleNDAclRuleType, 
				sleNDAclRuleRangeStartIPv6, sleNDAclRuleRangeEndIPv6, sleNDAclRuleIPv6Address, sleNDAclRuleIPv6Mask, sleNDAclRuleMacAddr, 
				sleNDAclRuleMacType }
			STATUS current
			DESCRIPTION 
				"createNDAclRule"
			::= { sleNDAclRuleNotifications 1 }

		
		sleNDAclRuleDestroyed NOTIFICATION-TYPE
			OBJECTS { sleNDAclRuleControlRequest, sleNDAclRuleControlTimeStamp, sleNDAclRuleControlReqResult, sleNDAclRuleControlAclIndex, sleNDAclRuleControlIndex
				 }
			STATUS current
			DESCRIPTION 
				"destroyNDAclRule"
			::= { sleNDAclRuleNotifications 2 }

		
		sleNDInspectVlan OBJECT IDENTIFIER ::= { sleNDInspection 4 }

		
		sleNDInspectVlanTable OBJECT-TYPE
			SYNTAX SEQUENCE OF SleNDInspectVlanEntry
			MAX-ACCESS not-accessible
			STATUS current
			DESCRIPTION
				"Description."
			::= { sleNDInspectVlan 1 }

		
		sleNDInspectVlanEntry OBJECT-TYPE
			SYNTAX SleNDInspectVlanEntry
			MAX-ACCESS not-accessible
			STATUS current
			DESCRIPTION
				"Description."
			INDEX { sleNDInspectVlanIndex }
			::= { sleNDInspectVlanTable 1 }

		
		SleNDInspectVlanEntry ::=
			SEQUENCE { 
				sleNDInspectVlanIndex
					Integer32,
				sleNDInspectVlanEnable
					INTEGER,
				sleNDInspectVlanFilterAclIndex
					Integer32,
				sleNDInspectVlanFwdPktCnt
					Integer32,
				sleNDInspectVlanDropPktCnt
					Integer32,
				sleNDInspectVlanAclPermits
					Integer32,
				sleNDInspectVlanAclDrops
					Integer32,
				sleNDInspectVlanDhcpv6Permits
					INTEGER,
				sleNDInspectVlanDhcpv6Denys
					INTEGER,
				sleNDInspectVlanLocalIpv6Denys
					INTEGER,
				sleNDInspectVlanFilterAclName
					OCTET STRING
			 }

		sleNDInspectVlanIndex OBJECT-TYPE
			SYNTAX Integer32 (1..4094)
			MAX-ACCESS read-only
			STATUS current
			DESCRIPTION
				"The index of vlan."
			::= { sleNDInspectVlanEntry 1 }

		
		sleNDInspectVlanEnable OBJECT-TYPE
			SYNTAX INTEGER
				{
				disable(0),
				enable(1)
				}
			MAX-ACCESS read-only
			STATUS current
			DESCRIPTION
				"The enable/disable control used per vlan."
			::= { sleNDInspectVlanEntry 2 }

		
		sleNDInspectVlanFilterAclIndex OBJECT-TYPE
			SYNTAX Integer32
			MAX-ACCESS read-only
			STATUS current
			DESCRIPTION
				"The ND acl index to be applied to vlan"
			::= { sleNDInspectVlanEntry 3 }

		
		sleNDInspectVlanFwdPktCnt OBJECT-TYPE
			SYNTAX Integer32
			MAX-ACCESS read-only
			STATUS current
			DESCRIPTION
				"Forwarded ND packet count."
			::= { sleNDInspectVlanEntry 4 }

		
		sleNDInspectVlanDropPktCnt OBJECT-TYPE
			SYNTAX Integer32
			MAX-ACCESS read-only
			STATUS current
			DESCRIPTION
				"Droped ND packet count."
			::= { sleNDInspectVlanEntry 5 }

		
		sleNDInspectVlanAclPermits OBJECT-TYPE
			SYNTAX Integer32
			MAX-ACCESS read-only
			STATUS current
			DESCRIPTION
				"Permited ND packet count by acl."
			::= { sleNDInspectVlanEntry 6 }

		
		sleNDInspectVlanAclDrops OBJECT-TYPE
			SYNTAX Integer32
			MAX-ACCESS read-only
			STATUS current
			DESCRIPTION
				"Droped ND packet count by acl."
			::= { sleNDInspectVlanEntry 7 }

		
		sleNDInspectVlanDhcpv6Permits OBJECT-TYPE
			SYNTAX INTEGER
			MAX-ACCESS read-only
			STATUS current
			DESCRIPTION
				"Permited ND packet count by DHCPv6 SNOOPING."
			::= { sleNDInspectVlanEntry 8 }

		
		sleNDInspectVlanDhcpv6Denys OBJECT-TYPE
			SYNTAX INTEGER
			MAX-ACCESS read-only
			STATUS current
			DESCRIPTION
				"Denyed ND packet count by DHCPv6 SNOOPING."
			::= { sleNDInspectVlanEntry 9 }

		
		sleNDInspectVlanLocalIpv6Denys OBJECT-TYPE
			SYNTAX INTEGER
			MAX-ACCESS read-only
			STATUS current
			DESCRIPTION
				"Denyed ND packet count by Local ipv6 address."
			::= { sleNDInspectVlanEntry 10 }

		
		sleNDInspectVlanFilterAclName OBJECT-TYPE
			SYNTAX OCTET STRING (SIZE (0..255))
			MAX-ACCESS read-only
			STATUS current
			DESCRIPTION
				"The name of acl to be applied to vlan."
			::= { sleNDInspectVlanEntry 11 }

		
		sleNDInspectVlanControl OBJECT IDENTIFIER ::= { sleNDInspectVlan 2 }

		
		sleNDInspectVlanControlRequest OBJECT-TYPE
			SYNTAX INTEGER
				{
				setNDInspectVlanProfile(1),
				clearNDInspectVlanStatistics(2)
				}
			MAX-ACCESS read-write
			STATUS current
			DESCRIPTION
				"Description"
			::= { sleNDInspectVlanControl 1 }

		
		sleNDInspectVlanControlStatus OBJECT-TYPE
			SYNTAX SleControlStatusType
			MAX-ACCESS read-only
			STATUS current
			DESCRIPTION
				"Description"
			::= { sleNDInspectVlanControl 2 }

		
		sleNDInspectVlanControlTimer OBJECT-TYPE
			SYNTAX Gauge32
			MAX-ACCESS read-write
			STATUS current
			DESCRIPTION
				"Description"
			::= { sleNDInspectVlanControl 3 }

		
		sleNDInspectVlanControlTimeStamp OBJECT-TYPE
			SYNTAX TimeTicks
			MAX-ACCESS read-only
			STATUS current
			DESCRIPTION
				"Description"
			::= { sleNDInspectVlanControl 4 }

		
		sleNDInspectVlanControlReqResult OBJECT-TYPE
			SYNTAX SleControlRequestResultType
			MAX-ACCESS read-only
			STATUS current
			DESCRIPTION
				"Result of the last command."
			::= { sleNDInspectVlanControl 5 }

		
		sleNDInspectVlanControlIndex OBJECT-TYPE
			SYNTAX INTEGER (1..4094)
			MAX-ACCESS read-write
			STATUS current
			DESCRIPTION
				"The index of vlan."
			::= { sleNDInspectVlanControl 6 }

		
		sleNDInspectVlanControlEnable OBJECT-TYPE
			SYNTAX INTEGER
				{
				disable(0),
				enable(1)
				}
			MAX-ACCESS read-write
			STATUS current
			DESCRIPTION
				"The enable/disable control used per vlan."
			::= { sleNDInspectVlanControl 7 }

		
		sleNDInspectVlanControlFilterAclIndex OBJECT-TYPE
			SYNTAX Integer32
			MAX-ACCESS read-write
			STATUS current
			DESCRIPTION
				"The ND Access-list index to be applied to vlan"
			::= { sleNDInspectVlanControl 8 }

		
		sleNDInspectVlanNotifications OBJECT IDENTIFIER ::= { sleNDInspectVlan 3 }

		
		sleNDInspectVlanChanged NOTIFICATION-TYPE
			OBJECTS { sleNDInspectVlanControlRequest, sleNDInspectVlanControlTimeStamp, sleNDInspectVlanControlReqResult, sleNDInspectVlanEnable, sleNDInspectVlanFilterAclIndex
				 }
			STATUS current
			DESCRIPTION 
				"setNDInspectVlanProfile"
			::= { sleNDInspectVlanNotifications 1 }

		
		sleNDInspectVlanStatsCleared NOTIFICATION-TYPE
			OBJECTS { sleNDInspectVlanControlRequest, sleNDInspectVlanControlTimeStamp, sleNDInspectVlanControlReqResult, sleNDInspectVlanControlIndex }
			STATUS current
			DESCRIPTION 
				"clearNDInspectVlanStatistics"
			::= { sleNDInspectVlanNotifications 2 }

		
		sleNDInspectPort OBJECT IDENTIFIER ::= { sleNDInspection 5 }

		
		sleNDInspectPortTable OBJECT-TYPE
			SYNTAX SEQUENCE OF SleNDInspectPortEntry
			MAX-ACCESS not-accessible
			STATUS current
			DESCRIPTION
				"Description."
			::= { sleNDInspectPort 1 }

		
		sleNDInspectPortEntry OBJECT-TYPE
			SYNTAX SleNDInspectPortEntry
			MAX-ACCESS not-accessible
			STATUS current
			DESCRIPTION
				"Description."
			INDEX { sleNDInspectPortIndex }
			::= { sleNDInspectPortTable 1 }

		
		SleNDInspectPortEntry ::=
			SEQUENCE { 
				sleNDInspectPortIndex
					Integer32,
				sleNDInspectPortTrust
					INTEGER
			 }

		sleNDInspectPortIndex OBJECT-TYPE
			SYNTAX Integer32 (1..255)
			MAX-ACCESS read-only
			STATUS current
			DESCRIPTION
				"The index of port."
			::= { sleNDInspectPortEntry 1 }

		
		sleNDInspectPortTrust OBJECT-TYPE
			SYNTAX INTEGER
				{
				untrust(0),
				trust(1)
				}
			MAX-ACCESS read-only
			STATUS current
			DESCRIPTION
				"The trust/untrust control used per port."
			::= { sleNDInspectPortEntry 2 }

		
		sleNDInspectPortControl OBJECT IDENTIFIER ::= { sleNDInspectPort 2 }

		
		sleNDInspectPortControlRequest OBJECT-TYPE
			SYNTAX INTEGER { setNDInspectTrustPort(1) }
			MAX-ACCESS read-write
			STATUS current
			DESCRIPTION
				"Description"
			::= { sleNDInspectPortControl 1 }

		
		sleNDInspectPortControlStatus OBJECT-TYPE
			SYNTAX SleControlStatusType
			MAX-ACCESS read-only
			STATUS current
			DESCRIPTION
				"Description"
			::= { sleNDInspectPortControl 2 }

		
		sleNDInspectPortControlTimer OBJECT-TYPE
			SYNTAX Gauge32
			MAX-ACCESS read-write
			STATUS current
			DESCRIPTION
				"Description"
			::= { sleNDInspectPortControl 3 }

		
		sleNDInspectPortControlTimeStamp OBJECT-TYPE
			SYNTAX TimeTicks
			MAX-ACCESS read-only
			STATUS current
			DESCRIPTION
				"Description"
			::= { sleNDInspectPortControl 4 }

		
		sleNDInspectPortControlReqResult OBJECT-TYPE
			SYNTAX SleControlRequestResultType
			MAX-ACCESS read-only
			STATUS current
			DESCRIPTION
				"Result of the last command."
			::= { sleNDInspectPortControl 5 }

		
		sleNDInspectPortControlIndex OBJECT-TYPE
			SYNTAX INTEGER (1..255)
			MAX-ACCESS read-write
			STATUS current
			DESCRIPTION
				"The index of port."
			::= { sleNDInspectPortControl 6 }

		
		sleNDInspectPortControlTrust OBJECT-TYPE
			SYNTAX INTEGER
				{
				untrust(0),
				trust(1)
				}
			MAX-ACCESS read-write
			STATUS current
			DESCRIPTION
				"The enable/disable control used per port"
			::= { sleNDInspectPortControl 7 }

		
		sleNDInspectPortNotifications OBJECT IDENTIFIER ::= { sleNDInspectPort 3 }

		
		sleNDInspectPortChanged NOTIFICATION-TYPE
			OBJECTS { sleNDInspectPortControlRequest, sleNDInspectPortControlTimeStamp, sleNDInspectPortControlReqResult, sleNDInspectPortControlTrust }
			STATUS current
			DESCRIPTION 
				"setNDInspectTrustPort"
			::= { sleNDInspectPortNotifications 1 }

		
		sleNDInspectInvalidLog OBJECT IDENTIFIER ::= { sleNDInspection 6 }

		
		sleNDInspectInvalidLogTable OBJECT-TYPE
			SYNTAX SEQUENCE OF SleNDInspectInvalidLogEntry
			MAX-ACCESS not-accessible
			STATUS current
			DESCRIPTION
				"Description."
			::= { sleNDInspectInvalidLog 1 }

		
		sleNDInspectInvalidLogEntry OBJECT-TYPE
			SYNTAX SleNDInspectInvalidLogEntry
			MAX-ACCESS not-accessible
			STATUS current
			DESCRIPTION
				"Description."
			INDEX { sleArpInspectInvalidLogId }
			::= { sleNDInspectInvalidLogTable 1 }

		
		SleNDInspectInvalidLogEntry ::=
			SEQUENCE { 
				sleNDInspectInvalidLogId
					INTEGER,
				sleNDInspectInvalidLogReason
					INTEGER,
				sleNDInspectInvalidLogSamePktCnt
					Counter32,
				sleNDInspectInvalidLogPortNumber
					INTEGER,
				sleNDInspectInvalidLogVlanId
					INTEGER,
				sleNDInspectInvalidLogSenderMacAddr
					OCTET STRING,
				sleNDInspectInvalidLogSrcMacAddr
					OCTET STRING,
				sleNDInspectInvalidLogSenderIpv6Addr
					InetAddressIPv6,
				sleNDInspectInvalidLogDstIpv6Addr
					InetAddressIPv6,
				sleNDInspectInvalidLogLastRecvTime
					OCTET STRING,
				sleNDInspectInvalidLogNDType
					INTEGER
			 }

		sleNDInspectInvalidLogId OBJECT-TYPE
			SYNTAX INTEGER (0..65535)
			MAX-ACCESS read-only
			STATUS current
			DESCRIPTION
				"ND inspection invalid index."
			::= { sleNDInspectInvalidLogEntry 1 }

		
		sleNDInspectInvalidLogReason OBJECT-TYPE
			SYNTAX INTEGER
				{
				aliReasonNone(0),
				aliiReasonDhcpv6Permit(1),
				aliReasonDhcpv6Deny(2),
				aliReasonAclPermit(3),
				aliReasonAclDeny(4),
				aliReasonLocalIpv6Deny(5),
				aliReasonRAguardPermit(6),
				aliReasonRAguardDeny(7)
				}
			MAX-ACCESS read-only
			STATUS current
			DESCRIPTION
				"ND inspection invalid reason."
			::= { sleNDInspectInvalidLogEntry 2 }

		
		sleNDInspectInvalidLogSamePktCnt OBJECT-TYPE
			SYNTAX Counter32
			MAX-ACCESS read-only
			STATUS current
			DESCRIPTION
				"ND inspection invalid same packet counters."
			::= { sleNDInspectInvalidLogEntry 3 }

		
		sleNDInspectInvalidLogPortNumber OBJECT-TYPE
			SYNTAX INTEGER
			MAX-ACCESS read-only
			STATUS current
			DESCRIPTION
				"ND inspection invalid port number."
			::= { sleNDInspectInvalidLogEntry 4 }

		
		sleNDInspectInvalidLogVlanId OBJECT-TYPE
			SYNTAX INTEGER
			MAX-ACCESS read-only
			STATUS current
			DESCRIPTION
				"ND inspection invalid vlan id."
			::= { sleNDInspectInvalidLogEntry 5 }

		
		sleNDInspectInvalidLogSenderMacAddr OBJECT-TYPE
			SYNTAX OCTET STRING (SIZE (0..6))
			MAX-ACCESS read-only
			STATUS current
			DESCRIPTION
				"ND inspection invalid sender mac address."
			::= { sleNDInspectInvalidLogEntry 6 }

		
		sleNDInspectInvalidLogSrcMacAddr OBJECT-TYPE
			SYNTAX OCTET STRING (SIZE (0..6))
			MAX-ACCESS read-only
			STATUS current
			DESCRIPTION
				"ND inspection invalid source mac address."
			::= { sleNDInspectInvalidLogEntry 7 }

		
		sleNDInspectInvalidLogSenderIpv6Addr OBJECT-TYPE
			SYNTAX InetAddressIPv6
			MAX-ACCESS read-only
			STATUS current
			DESCRIPTION
				"ND inspection invalid sender IPv6 address."
			::= { sleNDInspectInvalidLogEntry 8 }

		
		sleNDInspectInvalidLogDstIpv6Addr OBJECT-TYPE
			SYNTAX InetAddressIPv6
			MAX-ACCESS read-only
			STATUS current
			DESCRIPTION
				"ND inspection invalid destination IPv6 address."
			::= { sleNDInspectInvalidLogEntry 9 }

		
		sleNDInspectInvalidLogLastRecvTime OBJECT-TYPE
			SYNTAX OCTET STRING
			MAX-ACCESS read-only
			STATUS current
			DESCRIPTION
				"ND inspection invalid packet last received time."
			::= { sleNDInspectInvalidLogEntry 10 }

		
		sleNDInspectInvalidLogNDType OBJECT-TYPE
			SYNTAX INTEGER
				{
				ndiscRouterSolicitation(1),
				ndiscRouteradvertisemetn(2),
				ndiscNeighbourSolicitation(3),
				ndiscNeighbourAdvertisement(4)
				}
			MAX-ACCESS read-only
			STATUS current
			DESCRIPTION
				"The Type of droped ND packet."
			::= { sleNDInspectInvalidLogEntry 11 }

		
		sleRAGuard OBJECT IDENTIFIER ::= { sleSecurity 13 }

		
		sleRAGuardPolicy OBJECT IDENTIFIER ::= { sleRAGuard 1 }

		
		sleRAGuardPolicyTable OBJECT-TYPE
			SYNTAX SEQUENCE OF SleRAGuardPolicyEntry
			MAX-ACCESS not-accessible
			STATUS current
			DESCRIPTION
				"Description."
			::= { sleRAGuardPolicy 1 }

		
		sleRAGuardPolicyEntry OBJECT-TYPE
			SYNTAX SleRAGuardPolicyEntry
			MAX-ACCESS not-accessible
			STATUS current
			DESCRIPTION
				"Description."
			INDEX { sleRAGuardPolicyIndex }
			::= { sleRAGuardPolicyTable 1 }

		
		SleRAGuardPolicyEntry ::=
			SEQUENCE { 
				sleRAGuardPolicyIndex
					INTEGER,
				sleRAGuardPolicyName
					OCTET STRING,
				sleRAGuardPolicyHoplimitMin
					INTEGER,
				sleRAGuardPolicyHoplimitMax
					INTEGER,
				sleRAGuardPolicyManagedFlag
					INTEGER,
				sleRAGuardPolicyOtherFlag
					INTEGER,
				sleRAGuardPolicyRouterPreference
					INTEGER,
				sleRAGuardPolicyMatchACLName
					OCTET STRING,
				sleRAGuardPolicyMatchPrefixName
					OCTET STRING
			 }

		sleRAGuardPolicyIndex OBJECT-TYPE
			SYNTAX INTEGER (1..2147483647)
			MAX-ACCESS read-only
			STATUS current
			DESCRIPTION
				"The Index of RAGuard Policy."
			::= { sleRAGuardPolicyEntry 1 }

		
		sleRAGuardPolicyName OBJECT-TYPE
			SYNTAX OCTET STRING (SIZE (1..255))
			MAX-ACCESS read-only
			STATUS current
			DESCRIPTION
				"The name of RAGuard Policy."
			::= { sleRAGuardPolicyEntry 2 }

		
		sleRAGuardPolicyHoplimitMin OBJECT-TYPE
			SYNTAX INTEGER (0..255)
			MAX-ACCESS read-only
			STATUS current
			DESCRIPTION
				"The minimize value of hop-limit"
			::= { sleRAGuardPolicyEntry 3 }

		
		sleRAGuardPolicyHoplimitMax OBJECT-TYPE
			SYNTAX INTEGER (0..255)
			MAX-ACCESS read-only
			STATUS current
			DESCRIPTION
				"The maximize value of hop-limit"
			::= { sleRAGuardPolicyEntry 4 }

		
		sleRAGuardPolicyManagedFlag OBJECT-TYPE
			SYNTAX INTEGER
				{
				off(0),
				on(1)
				}
			MAX-ACCESS read-only
			STATUS current
			DESCRIPTION
				" "
			::= { sleRAGuardPolicyEntry 5 }

		
		sleRAGuardPolicyOtherFlag OBJECT-TYPE
			SYNTAX INTEGER
				{
				off(0),
				on(1)
				}
			MAX-ACCESS read-only
			STATUS current
			DESCRIPTION
				" "
			::= { sleRAGuardPolicyEntry 6 }

		
		sleRAGuardPolicyRouterPreference OBJECT-TYPE
			SYNTAX INTEGER
				{
				medium(0),
				high(1),
				low(3)
				}
			MAX-ACCESS read-only
			STATUS current
			DESCRIPTION
				" "
			::= { sleRAGuardPolicyEntry 7 }

		
		sleRAGuardPolicyMatchACLName OBJECT-TYPE
			SYNTAX OCTET STRING (SIZE (0..255))
			MAX-ACCESS read-only
			STATUS current
			DESCRIPTION
				"Name of matched IPv6 ACL"
			::= { sleRAGuardPolicyEntry 8 }

		
		sleRAGuardPolicyMatchPrefixName OBJECT-TYPE
			SYNTAX OCTET STRING (SIZE (0..255))
			MAX-ACCESS read-only
			STATUS current
			DESCRIPTION
				"Name of matched Prefix-List"
			::= { sleRAGuardPolicyEntry 9 }

		
		sleRAGuardPolicyControl OBJECT IDENTIFIER ::= { sleRAGuardPolicy 2 }

		
		sleRAGuardPolicyControlRequest OBJECT-TYPE
			SYNTAX INTEGER
				{
				createRAGuardPolicy(1),
				destroyRAGuardPolicy(2),
				changeRAGuardPolicy(3)
				}
			MAX-ACCESS read-write
			STATUS current
			DESCRIPTION
				"Description"
			::= { sleRAGuardPolicyControl 1 }

		
		sleRAGuardPolicyControlStatus OBJECT-TYPE
			SYNTAX SleControlStatusType
			MAX-ACCESS read-only
			STATUS current
			DESCRIPTION
				"Description"
			::= { sleRAGuardPolicyControl 2 }

		
		sleRAGuardPolicyControlTimer OBJECT-TYPE
			SYNTAX Gauge32
			MAX-ACCESS read-write
			STATUS current
			DESCRIPTION
				"Description"
			::= { sleRAGuardPolicyControl 3 }

		
		sleRAGuardPolicyControlTimeStamp OBJECT-TYPE
			SYNTAX TimeTicks
			MAX-ACCESS read-only
			STATUS current
			DESCRIPTION
				"Description"
			::= { sleRAGuardPolicyControl 4 }

		
		sleRAGuardPolicyControlReqResult OBJECT-TYPE
			SYNTAX SleControlRequestResultType
			MAX-ACCESS read-only
			STATUS current
			DESCRIPTION
				"Result of the last command."
			::= { sleRAGuardPolicyControl 5 }

		
		sleRAGuardPolicyControlIndex OBJECT-TYPE
			SYNTAX Integer32
			MAX-ACCESS read-write
			STATUS current
			DESCRIPTION
				" The Index of RAGuard Policy."
			::= { sleRAGuardPolicyControl 6 }

		
		sleRAGuardPolicyControlName OBJECT-TYPE
			SYNTAX OCTET STRING (SIZE (1..255))
			MAX-ACCESS read-write
			STATUS current
			DESCRIPTION
				" The name of RA Guard Policy."
			::= { sleRAGuardPolicyControl 7 }

		
		sleRAGuardPolicyControlHoplimitMin OBJECT-TYPE
			SYNTAX Integer32 (0..255)
			MAX-ACCESS read-write
			STATUS current
			DESCRIPTION
				"The minimize value of hop-limit "
			::= { sleRAGuardPolicyControl 8 }

		
		sleRAGuardPolicyControlHoplimitMax OBJECT-TYPE
			SYNTAX Integer32 (0..255)
			MAX-ACCESS read-write
			STATUS current
			DESCRIPTION
				"The maxmize value of hop-limit"
			::= { sleRAGuardPolicyControl 9 }

		
		sleRAGuardPolicyControlManagedFlag OBJECT-TYPE
			SYNTAX INTEGER
				{
				off(0),
				on(1)
				}
			MAX-ACCESS read-write
			STATUS current
			DESCRIPTION
				"Description "
			::= { sleRAGuardPolicyControl 10 }

		
		sleRAGuardPolicyControlOtherFlag OBJECT-TYPE
			SYNTAX INTEGER
				{
				off(0),
				on(1)
				}
			MAX-ACCESS read-write
			STATUS current
			DESCRIPTION
				"Description "
			::= { sleRAGuardPolicyControl 11 }

		
		sleRAGuardPolicyControlRouterPreference OBJECT-TYPE
			SYNTAX INTEGER
				{
				medium(0),
				high(1),
				low(3)
				}
			MAX-ACCESS read-write
			STATUS current
			DESCRIPTION
				"Description "
			::= { sleRAGuardPolicyControl 12 }

		
		sleRAGuardPolicyControlMatchACLName OBJECT-TYPE
			SYNTAX OCTET STRING (SIZE (0..255))
			MAX-ACCESS read-write
			STATUS current
			DESCRIPTION
				"Name of matched IPv6 ACL"
			::= { sleRAGuardPolicyControl 13 }

		
		sleRAGuardPolicyControlMatchPrefixName OBJECT-TYPE
			SYNTAX OCTET STRING (SIZE (0..255))
			MAX-ACCESS read-write
			STATUS current
			DESCRIPTION
				"Name of matched Prefix-List"
			::= { sleRAGuardPolicyControl 14 }

		
		sleRAGuardPolicyNotifications OBJECT IDENTIFIER ::= { sleRAGuardPolicy 3 }

		
		sleRAGuardPolicyCreated NOTIFICATION-TYPE
			OBJECTS { sleRAGuardPolicyControlRequest, sleRAGuardPolicyControlTimeStamp, sleRAGuardPolicyControlReqResult, sleRAGuardPolicyControlName }
			STATUS current
			DESCRIPTION 
				"createRAGuardPolicy"
			::= { sleRAGuardPolicyNotifications 1 }

		
		sleRAGuardPolicyDestroyed NOTIFICATION-TYPE
			OBJECTS { sleRAGuardPolicyControlRequest, sleRAGuardPolicyControlTimeStamp, sleRAGuardPolicyControlReqResult, sleRAGuardPolicyControlIndex }
			STATUS current
			DESCRIPTION 
				"destroyRAGuardPolicy"
			::= { sleRAGuardPolicyNotifications 2 }

		
		sleRAGuardPolicyChanged NOTIFICATION-TYPE
			OBJECTS { sleRAGuardPolicyControlRequest, sleRAGuardPolicyControlTimeStamp, sleRAGuardPolicyControlReqResult, sleRAGuardPolicyControlName, sleRAGuardPolicyControlHoplimitMin, 
				sleRAGuardPolicyControlHoplimitMax, sleRAGuardPolicyControlManagedFlag, sleRAGuardPolicyControlOtherFlag, sleRAGuardPolicyControlRouterPreference, sleRAGuardPolicyControlMatchACLName, 
				sleRAGuardPolicyControlMatchPrefixName }
			STATUS current
			DESCRIPTION 
				"changeRAGuardPolicy"
			::= { sleRAGuardPolicyNotifications 3 }

		
		sleRAGuardVlan OBJECT IDENTIFIER ::= { sleRAGuard 2 }

		
		sleRAGuardVlanTable OBJECT-TYPE
			SYNTAX SEQUENCE OF SleRAGuardVlanEntry
			MAX-ACCESS not-accessible
			STATUS current
			DESCRIPTION
				"Description."
			::= { sleRAGuardVlan 1 }

		
		sleRAGuardVlanEntry OBJECT-TYPE
			SYNTAX SleRAGuardVlanEntry
			MAX-ACCESS not-accessible
			STATUS current
			DESCRIPTION
				"Description."
			INDEX { sleRAGuardVlanIndex }
			::= { sleRAGuardVlanTable 1 }

		
		SleRAGuardVlanEntry ::=
			SEQUENCE { 
				sleRAGuardVlanIndex
					Integer32,
				sleRAGuardVlanEnable
					INTEGER,
				sleRAGuardVlanFilterPolicy
					Integer32,
				sleRAGuardVlanFilterAclName
					OCTET STRING
			 }

		sleRAGuardVlanIndex OBJECT-TYPE
			SYNTAX Integer32 (1..4094)
			MAX-ACCESS read-only
			STATUS current
			DESCRIPTION
				"The index of vlan."
			::= { sleRAGuardVlanEntry 1 }

		
		sleRAGuardVlanEnable OBJECT-TYPE
			SYNTAX INTEGER
				{
				disable(0),
				enable(1)
				}
			MAX-ACCESS read-only
			STATUS current
			DESCRIPTION
				"The enable/disable control used per vlan."
			::= { sleRAGuardVlanEntry 2 }

		
		sleRAGuardVlanFilterPolicy OBJECT-TYPE
			SYNTAX Integer32
			MAX-ACCESS read-only
			STATUS current
			DESCRIPTION
				"The RAGuard Policy Index to be applied to vlan"
			::= { sleRAGuardVlanEntry 3 }

		
		sleRAGuardVlanFilterAclName OBJECT-TYPE
			SYNTAX OCTET STRING (SIZE (1..255))
			MAX-ACCESS read-only
			STATUS current
			DESCRIPTION
				"The RAGuard Policy name to be applied to vlan"
			::= { sleRAGuardVlanEntry 4 }

		
		sleRAGuardVlanControl OBJECT IDENTIFIER ::= { sleRAGuardVlan 2 }

		
		sleRAGuardVlanControlRequest OBJECT-TYPE
			SYNTAX INTEGER { setRAGuardtVlanProfile(1) }
			MAX-ACCESS read-write
			STATUS current
			DESCRIPTION
				"Description"
			::= { sleRAGuardVlanControl 1 }

		
		sleRAGuardVlanControlStatus OBJECT-TYPE
			SYNTAX SleControlStatusType
			MAX-ACCESS read-only
			STATUS current
			DESCRIPTION
				"Description"
			::= { sleRAGuardVlanControl 2 }

		
		sleRAGuardVlanControlTimer OBJECT-TYPE
			SYNTAX Gauge32
			MAX-ACCESS read-write
			STATUS current
			DESCRIPTION
				"Description"
			::= { sleRAGuardVlanControl 3 }

		
		sleRAGuardVlanControlTimeStamp OBJECT-TYPE
			SYNTAX TimeTicks
			MAX-ACCESS read-only
			STATUS current
			DESCRIPTION
				"Description"
			::= { sleRAGuardVlanControl 4 }

		
		sleRAGuardVlanControlReqResult OBJECT-TYPE
			SYNTAX SleControlRequestResultType
			MAX-ACCESS read-only
			STATUS current
			DESCRIPTION
				"Result of the last command."
			::= { sleRAGuardVlanControl 5 }

		
		sleRAGuardVlanControlIndex OBJECT-TYPE
			SYNTAX INTEGER (1..4094)
			MAX-ACCESS read-write
			STATUS current
			DESCRIPTION
				"The index of vlan."
			::= { sleRAGuardVlanControl 6 }

		
		sleRAGuardVlanControlEnable OBJECT-TYPE
			SYNTAX INTEGER
				{
				disable(0),
				enable(1)
				}
			MAX-ACCESS read-write
			STATUS current
			DESCRIPTION
				"The enable/disable control used per vlan."
			::= { sleRAGuardVlanControl 7 }

		
		sleRAGuardVlanControlFilterPolicy OBJECT-TYPE
			SYNTAX Integer32
			MAX-ACCESS read-write
			STATUS current
			DESCRIPTION
				"The RAGuard Policy Index to be applied to vlan"
			::= { sleRAGuardVlanControl 8 }

		
		sleRAGuardVlanNotifications OBJECT IDENTIFIER ::= { sleRAGuardVlan 3 }

		
		sleRAGuardVlanChanged NOTIFICATION-TYPE
			OBJECTS { sleRAGuardVlanControlRequest, sleRAGuardVlanControlTimeStamp, sleRAGuardVlanControlReqResult, sleRAGuardVlanControlEnable, sleRAGuardVlanControlFilterPolicy
				 }
			STATUS current
			DESCRIPTION 
				"setNDInspectVlanProfile"
			::= { sleRAGuardVlanNotifications 1 }

		
		sleRAGuardPort OBJECT IDENTIFIER ::= { sleRAGuard 3 }

		
		sleRAGuardPortTable OBJECT-TYPE
			SYNTAX SEQUENCE OF SleRAGuardPortEntry
			MAX-ACCESS not-accessible
			STATUS current
			DESCRIPTION
				"Description."
			::= { sleRAGuardPort 1 }

		
		sleRAGuardPortEntry OBJECT-TYPE
			SYNTAX SleRAGuardPortEntry
			MAX-ACCESS not-accessible
			STATUS current
			DESCRIPTION
				"Description."
			INDEX { sleRAGuardPortIndex }
			::= { sleRAGuardPortTable 1 }

		
		SleRAGuardPortEntry ::=
			SEQUENCE { 
				sleRAGuardPortIndex
					Integer32,
				sleRAGuardPortTrust
					INTEGER
			 }

		sleRAGuardPortIndex OBJECT-TYPE
			SYNTAX Integer32 (1..1024)
			MAX-ACCESS read-only
			STATUS current
			DESCRIPTION
				"The index of port."
			::= { sleRAGuardPortEntry 1 }

		
		sleRAGuardPortTrust OBJECT-TYPE
			SYNTAX INTEGER
				{
				unknown(0),
				trust(1),
				untrust(2)
				}
			MAX-ACCESS read-only
			STATUS current
			DESCRIPTION
				"The trust/untrust/unknown control used per port."
			::= { sleRAGuardPortEntry 2 }

		
		sleRAGuardPortControl OBJECT IDENTIFIER ::= { sleRAGuardPort 2 }

		
		sleRAGuardPortControlRequest OBJECT-TYPE
			SYNTAX INTEGER { setdRAGuardTrustPort(1) }
			MAX-ACCESS read-write
			STATUS current
			DESCRIPTION
				"Description"
			::= { sleRAGuardPortControl 1 }

		
		sleRAGuardPortControlStatus OBJECT-TYPE
			SYNTAX SleControlStatusType
			MAX-ACCESS read-only
			STATUS current
			DESCRIPTION
				"Description"
			::= { sleRAGuardPortControl 2 }

		
		sleRAGuardPortControlTimer OBJECT-TYPE
			SYNTAX Gauge32
			MAX-ACCESS read-write
			STATUS current
			DESCRIPTION
				"Description"
			::= { sleRAGuardPortControl 3 }

		
		sleRAGuardPortControlTimeStamp OBJECT-TYPE
			SYNTAX TimeTicks
			MAX-ACCESS read-only
			STATUS current
			DESCRIPTION
				"Description"
			::= { sleRAGuardPortControl 4 }

		
		sleRAGuardPortControlReqResult OBJECT-TYPE
			SYNTAX SleControlRequestResultType
			MAX-ACCESS read-only
			STATUS current
			DESCRIPTION
				"Result of the last command."
			::= { sleRAGuardPortControl 5 }

		
		sleRAGuardPortControlIndex OBJECT-TYPE
			SYNTAX INTEGER (1..1024)
			MAX-ACCESS read-write
			STATUS current
			DESCRIPTION
				"The index of port."
			::= { sleRAGuardPortControl 6 }

		
		sleRAGuardPortControlTrust OBJECT-TYPE
			SYNTAX INTEGER
				{
				unknown(0),
				trust(1),
				untrust(2)
				}
			MAX-ACCESS read-write
			STATUS current
			DESCRIPTION
				"The trust/untrust/unknown control used per port."
			::= { sleRAGuardPortControl 7 }

		
		sleRAGuardPortNotifications OBJECT IDENTIFIER ::= { sleRAGuardPort 3 }

		
		sleRAGuardPortChanged NOTIFICATION-TYPE
			OBJECTS { sleRAGuardPortControlRequest, sleRAGuardPortControlTimeStamp, sleRAGuardPortControlReqResult, sleRAGuardPortControlTrust }
			STATUS current
			DESCRIPTION 
				"setNDInspectTrustPort"
			::= { sleRAGuardPortNotifications 1 }

		
		sleRadiusServerDot1x OBJECT IDENTIFIER ::= { sleSecurity 14 }

		
		sleRadiusServerDot1xTable OBJECT-TYPE
			SYNTAX SEQUENCE OF SleRadiusServerDot1xEntry
			MAX-ACCESS not-accessible
			STATUS current
			DESCRIPTION
				"Description."
			::= { sleRadiusServerDot1x 1 }

		
		sleRadiusServerDot1xEntry OBJECT-TYPE
			SYNTAX SleRadiusServerDot1xEntry
			MAX-ACCESS not-accessible
			STATUS current
			DESCRIPTION
				"Description."
			INDEX { sleRadiusServerDot1xAddress, sleRadiusServerDot1xAuthPort }
			::= { sleRadiusServerDot1xTable 1 }

		
		SleRadiusServerDot1xEntry ::=
			SEQUENCE { 
				sleRadiusServerDot1xAddress
					IpAddress,
				sleRadiusServerDot1xAuthPort
					INTEGER,
				sleRadiusServerDot1xTimeout
					INTEGER,
				sleRadiusServerDot1xRetransmit
					INTEGER,
				sleRadiusServerDot1xClientKey
					OCTET STRING
			 }

		sleRadiusServerDot1xAddress OBJECT-TYPE
			SYNTAX IpAddress
			MAX-ACCESS read-only
			STATUS current
			DESCRIPTION
				"The IP address of the RADIUS server referred 
				to in this table entry."
			::= { sleRadiusServerDot1xEntry 1 }

		
		sleRadiusServerDot1xAuthPort OBJECT-TYPE
			SYNTAX INTEGER (0..65535)
			MAX-ACCESS read-only
			STATUS current
			DESCRIPTION
				"The UDP port the client is using to send requests to this server for authentication."
			::= { sleRadiusServerDot1xEntry 2 }

		
		sleRadiusServerDot1xTimeout OBJECT-TYPE
			SYNTAX INTEGER (1..1000)
			MAX-ACCESS read-only
			STATUS current
			DESCRIPTION
				"RADIUS server timeout in secs"
			::= { sleRadiusServerDot1xEntry 3 }

		
		sleRadiusServerDot1xRetransmit OBJECT-TYPE
			SYNTAX INTEGER (1..100)
			MAX-ACCESS read-only
			STATUS current
			DESCRIPTION
				"RADIUS server retries"
			::= { sleRadiusServerDot1xEntry 4 }

		
		sleRadiusServerDot1xClientKey OBJECT-TYPE
			SYNTAX OCTET STRING (SIZE (0..255))
			MAX-ACCESS read-only
			STATUS current
			DESCRIPTION
				"The key to be used in communication between the 
				device and the Radius server."
			::= { sleRadiusServerDot1xEntry 5 }

		
		sleRadiusServerDot1xControl OBJECT IDENTIFIER ::= { sleRadiusServerDot1x 2 }

		
		sleRadiusServerDot1xControlRequest OBJECT-TYPE
			SYNTAX INTEGER
				{
				createRadiusServerDot1x(1),
				destroyRadiusServerDot1x(2),
				setRadiusServerDot1xProfile(3)
				}
			MAX-ACCESS read-write
			STATUS current
			DESCRIPTION
				"The MIB object for the user command."
			::= { sleRadiusServerDot1xControl 1 }

		
		sleRadiusServerDot1xControlStatus OBJECT-TYPE
			SYNTAX SleControlStatusType
			MAX-ACCESS read-only
			STATUS current
			DESCRIPTION
				"Describes the status of a user command group, 
				used for block commands while a command execution in process."
			::= { sleRadiusServerDot1xControl 2 }

		
		sleRadiusServerDot1xControlTimer OBJECT-TYPE
			SYNTAX Gauge32
			MAX-ACCESS read-write
			STATUS current
			DESCRIPTION
				"Maximum command duration time in case of long running"
			::= { sleRadiusServerDot1xControl 3 }

		
		sleRadiusServerDot1xControlTimeStamp OBJECT-TYPE
			SYNTAX TimeStamp
			MAX-ACCESS read-only
			STATUS current
			DESCRIPTION
				"Time stamp attribute set at end of command."
			::= { sleRadiusServerDot1xControl 4 }

		
		sleRadiusServerDot1xControlReqResult OBJECT-TYPE
			SYNTAX SleControlRequestResultType
			MAX-ACCESS read-only
			STATUS current
			DESCRIPTION
				"Command result attribute."
			::= { sleRadiusServerDot1xControl 5 }

		
		sleRadiusServerDot1xControlAddress OBJECT-TYPE
			SYNTAX IpAddress
			MAX-ACCESS read-write
			STATUS current
			DESCRIPTION
				"The IP address of the RADIUS server referred to 
				in this table entry."
			::= { sleRadiusServerDot1xControl 6 }

		
		sleRadiusServerDot1xControlAuthPort OBJECT-TYPE
			SYNTAX Integer32 (0..65535)
			MAX-ACCESS read-write
			STATUS current
			DESCRIPTION
				"The service port  number for communication with server."
			::= { sleRadiusServerDot1xControl 7 }

		
		sleRadiusServerDot1xControlTimeout OBJECT-TYPE
			SYNTAX Integer32 (1..1000)
			MAX-ACCESS read-write
			STATUS current
			DESCRIPTION
				"RADIUS server timeout in secs"
			::= { sleRadiusServerDot1xControl 8 }

		
		sleRadiusServerDot1xControlRetransmit OBJECT-TYPE
			SYNTAX Integer32 (1..100)
			MAX-ACCESS read-write
			STATUS current
			DESCRIPTION
				"RADIUS server retries"
			::= { sleRadiusServerDot1xControl 9 }

		
		sleRadiusServerDot1xControlClientKey OBJECT-TYPE
			SYNTAX OCTET STRING (SIZE (0..255))
			MAX-ACCESS read-write
			STATUS current
			DESCRIPTION
				"The key to be used in communication between 
				the device and the Radius server."
			::= { sleRadiusServerDot1xControl 10 }


		sleKeyChain OBJECT IDENTIFIER ::= { sleSecurity 15 }

		
		sleKeyChainTable OBJECT-TYPE
			SYNTAX SEQUENCE OF SleKeyChainEntry
			MAX-ACCESS not-accessible
			STATUS current
			DESCRIPTION
				"Description."
			::= { sleKeyChain 1 }

		
		sleKeyChainEntry OBJECT-TYPE
			SYNTAX SleKeyChainEntry
			MAX-ACCESS not-accessible
			STATUS current
			DESCRIPTION
				"Description."
			INDEX { sleKeyChainName, sleKeyChainKeyId }
			::= { sleKeyChainTable 1 }

		
		SleKeyChainEntry ::=
			SEQUENCE { 
				sleKeyChainName
					OCTET STRING,
				sleKeyChainKeyId
					Integer32,
				sleKeyChainKeyString
					OCTET STRING,
				sleKeyChainKeyAccepLifeTimeStartTime
					OCTET STRING,
				sleKeyChainKeyAcceptLifeTimeStartDay
					Integer32,
				sleKeyChainKeyAcceptLifeTimeStartMonth
					INTEGER,
				sleKeyChainKeyAcceptLifeTimeStartYear
					INTEGER,
				sleKeyChainKeyAcceptLifeTimeExpireType
					INTEGER,
				sleKeyChainKeyAcceptLifeTimeExpireTime
					OCTET STRING,
				sleKeyChainKeyAcceptLifeTimeExpireDay
					INTEGER,
				sleKeyChainKeyAcceptLifeTimeExpireMonth
					INTEGER,
				sleKeyChainKeyAcceptLifeTimeExpireYear
					INTEGER,
				sleKeyChainKeySendLifeTimeStartTime
					OCTET STRING,
				sleKeyChainKeySendLifeTimeStartDay
					Integer32,
				sleKeyChainKeySendLifeTimeStartMonth
					INTEGER,
				sleKeyChainKeySendLifeTimeStartYear
					INTEGER,
				sleKeyChainKeySendLifeTimeExpireType
					INTEGER,
				sleKeyChainKeySendLifeTimeExpireTime
					OCTET STRING,
				sleKeyChainKeySendLifeTimeExpireDay
					INTEGER,
				sleKeyChainKeySendLifeTimeExpireMonth
					INTEGER,
				sleKeyChainKeySendLifeTimeExpireYear
					INTEGER
			 }

		sleKeyChainName OBJECT-TYPE
			SYNTAX OCTET STRING
			MAX-ACCESS read-only
			STATUS current
			DESCRIPTION
				"Description."
			::= { sleKeyChainEntry 1 }

		
		sleKeyChainKeyId OBJECT-TYPE
			SYNTAX Integer32 (0..2147483647)
			MAX-ACCESS read-only
			STATUS current
			DESCRIPTION
				"Description."
			::= { sleKeyChainEntry 2 }

		
		sleKeyChainKeyString OBJECT-TYPE
			SYNTAX OCTET STRING
			MAX-ACCESS read-only
			STATUS current
			DESCRIPTION
				"Description."
			::= { sleKeyChainEntry 3 }

		
		sleKeyChainKeyAccepLifeTimeStartTime OBJECT-TYPE
			SYNTAX OCTET STRING
			MAX-ACCESS read-only
			STATUS current
			DESCRIPTION
				"Description."
			::= { sleKeyChainEntry 4 }

		
		sleKeyChainKeyAcceptLifeTimeStartDay OBJECT-TYPE
			SYNTAX Integer32 (1..31)
			MAX-ACCESS read-only
			STATUS current
			DESCRIPTION
				"Description."
			::= { sleKeyChainEntry 5 }

		
		sleKeyChainKeyAcceptLifeTimeStartMonth OBJECT-TYPE
			SYNTAX INTEGER
				{
				jan(1),
				feb(2),
				mar(3),
				apr(4),
				may(5),
				jun(6),
				jul(7),
				aug(8),
				sep(9),
				oct(10),
				nov(11),
				dec(12)
				}
			MAX-ACCESS read-only
			STATUS current
			DESCRIPTION
				"Description."
			::= { sleKeyChainEntry 6 }

		
		sleKeyChainKeyAcceptLifeTimeStartYear OBJECT-TYPE
			SYNTAX INTEGER (1993..2035)
			MAX-ACCESS read-only
			STATUS current
			DESCRIPTION
				"Description."
			::= { sleKeyChainEntry 7 }

		
		sleKeyChainKeyAcceptLifeTimeExpireType OBJECT-TYPE
			SYNTAX INTEGER
				{
				expire(0),
				neverexpire(1)
				}
			MAX-ACCESS read-only
			STATUS current
			DESCRIPTION
				"Description."
			::= { sleKeyChainEntry 8 }

		
		sleKeyChainKeyAcceptLifeTimeExpireTime OBJECT-TYPE
			SYNTAX OCTET STRING
			MAX-ACCESS read-only
			STATUS current
			DESCRIPTION
				"Description."
			::= { sleKeyChainEntry 9 }

		
		sleKeyChainKeyAcceptLifeTimeExpireDay OBJECT-TYPE
			SYNTAX INTEGER (1..31)
			MAX-ACCESS read-only
			STATUS current
			DESCRIPTION
				"Description."
			::= { sleKeyChainEntry 10 }

		
		sleKeyChainKeyAcceptLifeTimeExpireMonth OBJECT-TYPE
			SYNTAX INTEGER
				{
				jan(1),
				feb(2),
				mar(3),
				apr(4),
				may(5),
				jun(6),
				jul(7),
				aug(8),
				sep(9),
				oct(10),
				nov(11),
				dec(12)
				}
			MAX-ACCESS read-only
			STATUS current
			DESCRIPTION
				"Description."
			::= { sleKeyChainEntry 11 }

		
		sleKeyChainKeyAcceptLifeTimeExpireYear OBJECT-TYPE
			SYNTAX INTEGER (1993..2035)
			MAX-ACCESS read-only
			STATUS current
			DESCRIPTION
				"Description."
			::= { sleKeyChainEntry 12 }

		
		sleKeyChainKeySendLifeTimeStartTime OBJECT-TYPE
			SYNTAX OCTET STRING
			MAX-ACCESS read-only
			STATUS current
			DESCRIPTION
				"Description."
			::= { sleKeyChainEntry 13 }

		
		sleKeyChainKeySendLifeTimeStartDay OBJECT-TYPE
			SYNTAX Integer32 (1..31)
			MAX-ACCESS read-only
			STATUS current
			DESCRIPTION
				"Description."
			::= { sleKeyChainEntry 14 }

		
		sleKeyChainKeySendLifeTimeStartMonth OBJECT-TYPE
			SYNTAX INTEGER
				{
				jan(1),
				feb(2),
				mar(3),
				apr(4),
				may(5),
				jun(6),
				jul(7),
				aug(8),
				sep(9),
				oct(10),
				nov(11),
				dec(12)
				}
			MAX-ACCESS read-only
			STATUS current
			DESCRIPTION
				"Description."
			::= { sleKeyChainEntry 15 }

		
		sleKeyChainKeySendLifeTimeStartYear OBJECT-TYPE
			SYNTAX INTEGER (1993..2035)
			MAX-ACCESS read-only
			STATUS current
			DESCRIPTION
				"Description."
			::= { sleKeyChainEntry 16 }

		
		sleKeyChainKeySendLifeTimeExpireType OBJECT-TYPE
			SYNTAX INTEGER
				{
				expire(0),
				neverexpire(1)
				}
			MAX-ACCESS read-only
			STATUS current
			DESCRIPTION
				"Description."
			::= { sleKeyChainEntry 17 }

		
		sleKeyChainKeySendLifeTimeExpireTime OBJECT-TYPE
			SYNTAX OCTET STRING
			MAX-ACCESS read-only
			STATUS current
			DESCRIPTION
				"Description."
			::= { sleKeyChainEntry 18 }

		
		sleKeyChainKeySendLifeTimeExpireDay OBJECT-TYPE
			SYNTAX INTEGER (1..31)
			MAX-ACCESS read-only
			STATUS current
			DESCRIPTION
				"Description."
			::= { sleKeyChainEntry 19 }

		
		sleKeyChainKeySendLifeTimeExpireMonth OBJECT-TYPE
			SYNTAX INTEGER
				{
				jan(1),
				feb(2),
				mar(3),
				apr(4),
				may(5),
				jun(6),
				jul(7),
				aug(8),
				sep(9),
				oct(10),
				nov(11),
				dec(12)
				}
			MAX-ACCESS read-only
			STATUS current
			DESCRIPTION
				"Description."
			::= { sleKeyChainEntry 20 }

		
		sleKeyChainKeySendLifeTimeExpireYear OBJECT-TYPE
			SYNTAX INTEGER (1993..2035)
			MAX-ACCESS read-only
			STATUS current
			DESCRIPTION
				"Description."
			::= { sleKeyChainEntry 21 }

		
		sleKeyChainControl OBJECT IDENTIFIER ::= { sleKeyChain 2 }

		
		sleKeyChainControlRequest OBJECT-TYPE
			SYNTAX INTEGER
				{
				createKeyChain(1),
				deleteKeyChain(2),
				createKeyChainKey(3),
				deleteKeyChainKey(4),
				setKeyChainKeyString(5),
				deleteKeyChainKeyString(6),
				setKeyChainKeyAcceptLifeTimeProfile(7),
				deleteKeyChainKeyAcceptLifeTime(8),
				setKeyChainKeySendLifeTimeProfile(9),
				deleteKeyChainKeySendLifeTime(10)
				}
			MAX-ACCESS read-write
			STATUS current
			DESCRIPTION
				"Description"
			::= { sleKeyChainControl 1 }

		
		sleKeyChainControlStatus OBJECT-TYPE
			SYNTAX SleControlStatusType
			MAX-ACCESS read-only
			STATUS current
			DESCRIPTION
				"Description"
			::= { sleKeyChainControl 2 }

		
		sleKeyChainControlTimer OBJECT-TYPE
			SYNTAX Gauge32
			MAX-ACCESS read-write
			STATUS current
			DESCRIPTION
				"Description"
			::= { sleKeyChainControl 3 }

		
		sleKeyChainControlTimeStamp OBJECT-TYPE
			SYNTAX TimeTicks
			MAX-ACCESS read-only
			STATUS current
			DESCRIPTION
				"Description"
			::= { sleKeyChainControl 4 }

		
		sleKeyChainControlReqResult OBJECT-TYPE
			SYNTAX SleControlRequestResultType
			MAX-ACCESS read-only
			STATUS current
			DESCRIPTION
				"Result of the last command."
			::= { sleKeyChainControl 5 }

		
		sleKeyChainControlName OBJECT-TYPE
			SYNTAX OCTET STRING
			MAX-ACCESS read-write
			STATUS current
			DESCRIPTION
				"Description."
			::= { sleKeyChainControl 6 }

		
		sleKeyChainControlKeyId OBJECT-TYPE
			SYNTAX Integer32 (0..2147483647)
			MAX-ACCESS read-write
			STATUS current
			DESCRIPTION
				"Description."
			::= { sleKeyChainControl 7 }

		
		sleKeyChainControlKeyString OBJECT-TYPE
			SYNTAX OCTET STRING
			MAX-ACCESS read-write
			STATUS current
			DESCRIPTION
				"Description."
			::= { sleKeyChainControl 8 }

		
		sleKeyChainControlKeyAcceptLifeTimeStartTime OBJECT-TYPE
			SYNTAX OCTET STRING
			MAX-ACCESS read-write
			STATUS current
			DESCRIPTION
				"Description."
			::= { sleKeyChainControl 9 }

		
		sleKeyChainControlKeyAcceptLifeTimeStartDay OBJECT-TYPE
			SYNTAX INTEGER (1..31)
			MAX-ACCESS read-write
			STATUS current
			DESCRIPTION
				"Description."
			::= { sleKeyChainControl 10 }

		
		sleKeyChainControlKeyAcceptLifeTimeStartMonth OBJECT-TYPE
			SYNTAX INTEGER
				{
				jan(1),
				feb(2),
				mar(3),
				apr(4),
				may(5),
				jun(6),
				jul(7),
				aug(8),
				sep(9),
				oct(10),
				nov(11),
				dec(12)
				}
			MAX-ACCESS read-write
			STATUS current
			DESCRIPTION
				"Description."
			::= { sleKeyChainControl 11 }

		
		sleKeyChainControlKeyAcceptLifeTimeStartYear OBJECT-TYPE
			SYNTAX INTEGER (1993..2035)
			MAX-ACCESS read-write
			STATUS current
			DESCRIPTION
				"Description."
			::= { sleKeyChainControl 12 }

		
		sleKeyChainControlKeyAcceptLifeTimeExpireType OBJECT-TYPE
			SYNTAX INTEGER
				{
				expire(0),
				neverexpire(1)
				}
			MAX-ACCESS read-write
			STATUS current
			DESCRIPTION
				"Description."
			::= { sleKeyChainControl 13 }

		
		sleKeyChainControlKeyAcceptLifeTimeExpireTime OBJECT-TYPE
			SYNTAX OCTET STRING
			MAX-ACCESS read-write
			STATUS current
			DESCRIPTION
				"Description."
			::= { sleKeyChainControl 14 }

		
		sleKeyChainControlKeyAcceptLifeTimeExpireDay OBJECT-TYPE
			SYNTAX INTEGER (1..31)
			MAX-ACCESS read-write
			STATUS current
			DESCRIPTION
				"Description."
			::= { sleKeyChainControl 15 }

		
		sleKeyChainControlKeyAcceptLifeTimeExpireMonth OBJECT-TYPE
			SYNTAX INTEGER
				{
				jan(1),
				feb(2),
				mar(3),
				apr(4),
				may(5),
				jun(6),
				jul(7),
				aug(8),
				sep(9),
				oct(10),
				nov(11),
				dec(12)
				}
			MAX-ACCESS read-write
			STATUS current
			DESCRIPTION
				"Description."
			::= { sleKeyChainControl 16 }

		
		sleKeyChainControlKeyAcceptLifeTimeExpireYear OBJECT-TYPE
			SYNTAX INTEGER (1993..2035)
			MAX-ACCESS read-write
			STATUS current
			DESCRIPTION
				"Description."
			::= { sleKeyChainControl 17 }

		
		sleKeyChainControlKeySendLifeTimeStartTime OBJECT-TYPE
			SYNTAX OCTET STRING
			MAX-ACCESS read-write
			STATUS current
			DESCRIPTION
				"Description."
			::= { sleKeyChainControl 18 }

		
		sleKeyChainControlKeySendLifeTimeStartDay OBJECT-TYPE
			SYNTAX INTEGER (1..31)
			MAX-ACCESS read-write
			STATUS current
			DESCRIPTION
				"Description."
			::= { sleKeyChainControl 19 }

		
		sleKeyChainControlKeySendLifeTimeStartMonth OBJECT-TYPE
			SYNTAX INTEGER
				{
				jan(1),
				feb(2),
				mar(3),
				apr(4),
				may(5),
				jun(6),
				jul(7),
				aug(8),
				sep(9),
				oct(10),
				nov(11),
				dec(12)
				}
			MAX-ACCESS read-write
			STATUS current
			DESCRIPTION
				"Description."
			::= { sleKeyChainControl 20 }

		
		sleKeyChainControlKeySendLifeTimeStartYear OBJECT-TYPE
			SYNTAX INTEGER (1993..2035)
			MAX-ACCESS read-write
			STATUS current
			DESCRIPTION
				"Description."
			::= { sleKeyChainControl 21 }

		
		sleKeyChainControlKeySendLifeTimeExpireType OBJECT-TYPE
			SYNTAX INTEGER
				{
				expire(0),
				neverexpire(1)
				}
			MAX-ACCESS read-write
			STATUS current
			DESCRIPTION
				"Description."
			::= { sleKeyChainControl 22 }

		
		sleKeyChainControlKeySendLifeTimeExpireTime OBJECT-TYPE
			SYNTAX OCTET STRING
			MAX-ACCESS read-write
			STATUS current
			DESCRIPTION
				"Description."
			::= { sleKeyChainControl 23 }

		
		sleKeyChainControlKeySendLifeTimeExpireDay OBJECT-TYPE
			SYNTAX INTEGER (1..31)
			MAX-ACCESS read-write
			STATUS current
			DESCRIPTION
				"Description."
			::= { sleKeyChainControl 24 }

		
		sleKeyChainControlKeySendLifeTimeExpireMonth OBJECT-TYPE
			SYNTAX INTEGER
				{
				jan(1),
				feb(2),
				mar(3),
				apr(4),
				may(5),
				jun(6),
				jul(7),
				aug(8),
				sep(9),
				oct(10),
				nov(11),
				dec(12)
				}
			MAX-ACCESS read-write
			STATUS current
			DESCRIPTION
				"Description."
			::= { sleKeyChainControl 25 }

		
		sleKeyChainControlKeySendLifeTimeExpireYear OBJECT-TYPE
			SYNTAX INTEGER (1993..2035)
			MAX-ACCESS read-write
			STATUS current
			DESCRIPTION
				"Description."
			::= { sleKeyChainControl 26 }

		
		sleSecurityGroup OBJECT-GROUP
			OBJECTS { sleSecurityRadiusRetransmissions, sleSecurityRadiusTimeouts, sleSecurityRadiusInterfaceName, sleSecurityRadiusInterfaceAddress, sleSecurityTacacsInterfaceName, 
				sleSecurityTacacsInterfaceAddress, sleSecurityTacacsPort, sleSecurityTacacsAuthType, sleSecurityTacacsTimeouts, sleSecurityTacacsPriorityLevel, 
				sleSecurityDot1xActivity, sleSecurityLoginLimits, sleSecurityControlRequest, sleSecurityControlStatus, sleSecurityControlTimer, 
				sleSecurityControlTimeStamp, sleSecurityControlReqResult, sleSecurityControlRadiusRetransmissions, sleSecurityControlRadiusTimeouts, sleSecurityControlRadiusInterfaceName, 
				sleSecurityControlRadiusInterfaceAddress, sleSecurityControlTacacsInterfaceName, sleSecurityControlTacacsInterfaceAddress, sleSecurityControlTacacsPort, sleSecurityControlTacacsAuthType, 
				sleSecurityControlTacacsTimeouts, sleSecurityControlTacacsPriorityLevel, sleSecurityControlDot1xActivity, sleSecurityControlLoginLimits, sleAaaSession, 
				sleAaaAuthen, sleAaaEnable, sleAaaPrimarySequence, sleAaaControlRequest, sleAaaControlStatus, 
				sleAaaControlTimer, sleAaaControlTimeStamp, sleAaaControlReqResult, sleAaaControlSession, sleAaaControlAuthen, 
				sleAaaControlEnable, sleAaaControlPrimaryFlag, sleRadiusServerAddress, sleRadiusServerClientKey, sleRadiusServerAuthPort, 
				sleRadiusServerAccPort, sleRadiusServerMode, sleRadiusServerControlRequest, sleRadiusServerControlStatus, sleRadiusServerControlTimer, 
				sleRadiusServerControlTimeStamp, sleRadiusServerControlReqResult, sleRadiusServerControlAddress, sleRadiusServerControlClientKey, sleRadiusServerControlAuthPort, 
				sleRadiusServerControlAccPort, sleRadiusServerControlMode, sleTacacsServerAddress, sleTacacsServerClientKey, sleTacacsServerControlRequest, 
				sleTacacsServerControlStatus, sleTacacsServerControlTimer, sleTacacsServerControlTimeStamp, sleTacacsServerControlReqResult, sleTacacsServerControlAddress, 
				sleTacacsServerControlClientKey, sleAclName, sleAclSrcIpAddr, sleAclSrcPrefixLength, sleAclDstIpAddr, 
				sleAclDstPrefixLength, sleAclDscp, sleAclProtocolType, sleAclTcpFlag, sleAclSrcL4Port, 
				sleAclDstL4Port, sleAclPktLen, sleAclValidFlags, sleAclMatchFlags, sleAclMatchAction, 
				sleAclNomatchAction, sleAclPriority, sleAclControlReqest, sleAclControlStatus, sleAclControlTimer, 
				sleAclControlTimeStamp, sleAclControlReqResult, sleAclControlName, sleAclControlSrcIpAddr, sleAclControlSrcPrefixLength, 
				sleAclControlDstIpAddr, sleAclControlDstPrefixLength, sleAclControlDscp, sleAclControlProtocolType, sleAclControlTcpFlag, 
				sleAclControlSrcL4Port, sleAclControlDstL4Port, sleAclControlPktLen, sleAclControlValidFlags, sleAclControlMatchFlags, 
				sleAclControlMatchAction, sleAclControlNomatchAction, sleAclControlPriority, sleDot1xPortIndex, sleDot1xPortEnable, 
				sleDot1xPortMode, sleDot1xPortReauthEnable, sleDot1xPortQuietPeriod, sleDot1xPortReauthPeriod, sleDot1xPortAuthSuccess, 
				sleDot1xPortControlRequest, sleDot1xPortControlStatus, sleDot1xPortControlTimer, sleDot1xPortControlTimeStamp, sleDot1xPortControlReqResult, 
				sleDot1xPortControlIndex, sleDot1xPortControlEnable, sleDot1xPortControlMode, sleDot1xPortControlReauthEnable, sleDot1xPortControlQuietPeriod, 
				sleDot1xPortControlReauthPeriod, sleDot1xStatsPortIndex, sleDot1xStatsEapolFramesRx, sleDot1xStatsEapolFramesTx, sleDot1xStatsEapolStartFramesRx, 
				sleDot1xStatsEapolLogoffFramesRx, sleDot1xStatsEapolRespIdFramesRx, sleDot1xStatsEapolRespFramesRx, sleDot1xStatsEapolReqIdFramesTx, sleDot1xStatsEapolReqFramesTx, 
				sleDot1xStatsInvalidEapolFramesRx, sleDot1xStatsEapLengthErrorFramesRx, sleDot1xStatsLastEapolFrameVersion, sleDot1xStatsLastEapolFrameSource, sleDot1xStatsControlRequest, 
				sleDot1xStatsControlStatus, sleDot1xStatsControlTimer, sleDot1xStatsControlTimeStamp, sleDot1xStatsControlReqResult, sleDot1xStatsControlPortIndex, 
				sleArpInspectValidateSrcMac, sleArpInspectValidateDstMac, sleArpInspectValidateIpAddr, sleArpInspectLogBufferSize, sleArpInspectLogEntry, 
				sleArpInspectLogInterval, sleArpInspectControlRequest, sleArpInspectControlStatus, sleArpInspectControlTimer, sleArpInspectControlTimeStamp, 
				sleArpInspectControlReqResult, sleArpInspectControlValidateSrcMac, sleArpInspectControlValidateDstMac, sleArpInspectControlValidateIpAddr, sleArpInspectControlLogBufferSize, 
				sleArpInspectControlLogEntry, sleArpInspectControlLogInterval, sleArpAclIndex, sleArpAclName, sleArpAclNumEntries, 
				sleArpAclControlRequest, sleArpAclControlStatus, sleArpAclControlTimer, sleArpAclControlTimeStamp, sleArpAclControlReqResult, 
				sleArpAclControlIndex, sleArpAclControlName, sleArpAclRuleAclIndex, sleArpAclRuleIndex, sleArpAclRuleAction, 
				sleArpAclRuleType, sleArpAclRuleRangeStartIP, sleArpAclRuleRangeEndIP, sleArpAclRuleIPAddress, sleArpAclRuleIPMask, 
				sleArpAclRuleMacAddr, sleArpAclRuleMacType, sleArpAclRuleControlRequest, sleArpAclRuleControlStatus, sleArpAclRuleControlTimer, 
				sleArpAclRuleControlTimeStamp, sleArpAclRuleControlReqResult, sleArpAclRuleControlAclIndex, sleArpAclRuleControlIndex, sleArpAclRuleControlAction, 
				sleArpAclRuleControlType, sleArpAclRuleControlRangeStartIP, sleArpAclRuleControlRangeEndIP, sleArpAclRuleControlIPAddress, sleArpAclRuleControlIPMask, 
				sleArpAclRuleControlMacAddr, sleArpAclRuleControlMacType, sleArpInspectVlanIndex, sleArpInspectVlanEnable, sleArpInspectVlanFilterAcl, 
				sleArpInspectVlanFwdPktCnt, sleArpInspectVlanDropPktCnt, sleArpInspectVlanAclPermits, sleArpInspectVlanAclDrops, sleArpInspectVlanSrcMacFailurs, 
				sleArpInspectVlanDstMacFailurs, sleArpInspectVlanIpAddrFailurs, sleArpInspectVlanFilterAclName, sleArpInspectVlanControlRequest, sleArpInspectVlanControlStatus, 
				sleArpInspectVlanControlTimer, sleArpInspectVlanControlTimeStamp, sleArpInspectVlanControlReqResult, sleArpInspectVlanControlIndex, sleArpInspectVlanControlEnable, 
				sleArpInspectVlanControlFilterAcl, sleArpInspectPortIndex, sleArpInspectPortTrust, sleArpInspectPortControlRequest, sleArpInspectPortControlStatus, 
				sleArpInspectPortControlTimer, sleArpInspectPortControlTimeStamp, sleArpInspectPortControlReqResult, sleArpInspectPortControlIndex, sleArpInspectPortControlTrust, 
				sleArpInspectInvalidLogId, sleArpInspectInvalidLogReason, sleArpInspectInvalidLogSamePktCnt, sleArpInspectInvalidLogOpcode, sleArpInspectInvalidLogPortNumber, 
				sleArpInspectInvalidLogVlanId, sleArpInspectInvalidLogSrcMacAddr, sleArpInspectInvalidLogSrcIpAddr, sleArpInspectInvalidLogDstMacAddr, sleArpInspectInvalidLogDstIpAddr, 
				sleArpInspectInvalidLogLastRecvTime, sleSecurityAttackBasicBaseInfoGlobalStatus, sleSecurityAttackBasicBaseControlRequest, sleSecurityAttackBasicBaseControlStatus, sleSecurityAttackBasicBaseControlTimer, 
				sleSecurityAttackBasicBaseControlTimeStamp, sleSecurityAttackBasicBaseControlReqResult, sleSecurityAttackBasicBaseControlGlobalStatus, sleSecurityAttackBasicPolicyBlockTime, sleSecurityAttackBasicPolicyControlRequest, 
				sleSecurityAttackBasicPolicyControlStatus, sleSecurityAttackBasicPolicyControlTimer, sleSecurityAttackBasicPolicyControlTimeStamp, sleSecurityAttackBasicPolicyControlReqResult, sleSecurityAttackBasicPolicyControlAttackType, 
				sleSecurityAttackBasicPolicyControlBlockTime, sleSecurityAttackBasicExceptListIndex, sleSecurityAttackBasicExceptListProtocolType, sleSecurityAttackBasicExceptListSourceIpAddress, sleSecurityAttackBasicExceptListDestinationIpAddress, 
				sleSecurityAttackBasicExceptListControlRequest, sleSecurityAttackBasicExceptListControlStatus, sleSecurityAttackBasicExceptListControlTimer, sleSecurityAttackBasicExceptListControlTimeStamp, sleSecurityAttackBasicExceptListControlReqResult, 
				sleSecurityAttackBasicExceptListControlRuleIndex, sleSecurityAttackBasicExceptListControlProtocolType, sleSecurityAttackBasicExceptListControlSourceIpAddress, sleSecurityAttackBasicExceptListControlDestinationIpAddress, sleSecurityAttackBasicBlockedListIndex, 
				sleSecurityAttackBasicBlockedListAttackType, sleSecurityAttackBasicBlockedListStartTime, sleSecurityAttackBasicBlockedListEndTime, sleSecurityAttackBasicBlockedListAttackSourceIp, sleSecurityAttackBasicBlockedListAttackDestinationIp, 
				sleSecurityAttackBasicBlockedListProtocol, sleSecurityAttackBasicBlockedListAttackPktCount, sleSecurityAttackBasicBlockedListAttackBlockTime, sleSecurityAttackBasicBlockedListControlRequest, sleSecurityAttackBasicBlockedListControlStatus, 
				sleSecurityAttackBasicBlockedListControlTimer, sleSecurityAttackBasicBlockedListControlTimeStamp, sleSecurityAttackBasicBlockedListControlReqResult, sleSecurityAttackBasicBlockedListControlRuleIndex, sleSecurityAttackBasicBlockedListControlBlockTime, 
				sleSecurityAttackExpansionBaseGlobalStatus, sleSecurityAttackExpansionBaseControlRequest, sleSecurityAttackExpansionBaseControlStatus, sleSecurityAttackExpansionBaseControlTimer, sleSecurityAttackExpansionBaseControlTimeStamp, 
				sleSecurityAttackExpansionBaseControlReqResult, sleSecurityAttackExpansionBaseControlGlobalStatus, sleSecurityAttackExpansionPolicyPortIndex, sleSecurityAttackExpansionPolicyStatus, sleSecurityAttackExpansionPolicyAttackType, 
				sleSecurityAttackExpansionPolicyBlockTime, sleSecurityAttackExpansionPolicyControlRequest, sleSecurityAttackExpansionPolicyControlStatus, sleSecurityAttackExpansionPolicyControlTimer, sleSecurityAttackExpansionPolicyControlTimeStamp, 
				sleSecurityAttackExpansionPolicyControlReqResult, sleSecurityAttackExpansionPolicyControlPortIndex, sleSecurityAttackExpansionPolicyControlAttackType, sleSecurityAttackExpansionPolicyControlBlockTime, sleSecurityAttackExpansionExceptListPortIndex, 
				sleSecurityAttackExpansionExceptListIndex, sleSecurityAttackExpansionExceptListRuleIndex, sleSecurityAttackExpansionExceptListProtocolType, sleSecurityAttackExpansionExceptListSourceType, sleSecurityAttackExpansionExceptListSourceIpAddress, 
				sleSecurityAttackExpansionExceptListSourceIpMask, sleSecurityAttackExpansionExceptListSourceMac, sleSecurityAttackExpansionExceptListSourcePortType, sleSecurityAttackExpansionExceptListSourcePortFrom, sleSecurityAttackExpansionExceptListSourcePortTo, 
				sleSecurityAttackExpansionExceptListDestinationType, sleSecurityAttackExpansionExceptListDestinationIpAddress, sleSecurityAttackExpansionExceptListDestinationIpMask, sleSecurityAttackExpansionExceptListDestinationMac, sleSecurityAttackExpansionExceptListDestinationPortType, 
				sleSecurityAttackExpansionExceptListDestinationPortFrom, sleSecurityAttackExpansionExceptListDestinationPortTo, sleSecurityAttackExpansionExceptListControlRequest, sleSecurityAttackExpansionExceptListControlStatus, sleSecurityAttackExpansionExceptListControlTimer, 
				sleSecurityAttackExpansionExceptListControlTimeStamp, sleSecurityAttackExpansionExceptListControlReqResult, sleSecurityAttackExpansionExceptListControlPortIndex, sleSecurityAttackExpansionExceptListControlRuleIndex, sleSecurityAttackExpansionExceptListControlProtocolType, 
				sleSecurityAttackExpansionExceptListControlSourceType, sleSecurityAttackExpansionExceptListControlSourceIpAddress, sleSecurityAttackExpansionExceptListControlSourceIpMask, sleSecurityAttackExpansionExceptListControlSourceMac, sleSecurityAttackExpansionExceptListControlSourcePortType, 
				sleSecurityAttackExpansionExceptListControlSourcePortFrom, sleSecurityAttackExpansionExceptListControlSourcePortTo, sleSecurityAttackExpansionExceptListControlDestinationType, sleSecurityAttackExpansionExceptListControlDestinationIpAddress, sleSecurityAttackExpansionExceptListControlDestinationIpMask, 
				sleSecurityAttackExpansionExceptListControlDestinationMac, sleSecurityAttackExpansionExceptListControlDestinationPortType, sleSecurityAttackExpansionExceptListControlDestinationPortFrom, sleSecurityAttackExpansionExceptListControlDestinationPortTo, sleSecurityAttackExpansionBlockedListPortIndex, 
				sleSecurityAttackExpansionBlockedListIndex, sleSecurityAttackExpansionBlockedListRuleIndex, sleSecurityAttackExpansionBlockedListAttackType, sleSecurityAttackExpansionBlockedListAttackBlockType, sleSecurityAttackExpansionBlockedListStartTime, 
				sleSecurityAttackExpansionBlockedListEndTime, sleSecurityAttackExpansionBlockedListAttackSourceIp, sleSecurityAttackExpansionBlockedListSourceMac, sleSecurityAttackExpansionBlockedListAttackDestinationIp, sleSecurityAttackExpansionBlockedListProtocol, 
				sleSecurityAttackExpansionBlockedListSourcePort, sleSecurityAttackExpansionBlockedListDestinationPort, sleSecurityAttackExpansionBlockedListAttackPktCount, sleSecurityAttackExpansionBlockedListAttackBlockTime, sleSecurityAttackExpansionBlockedListControlRequest, 
				sleSecurityAttackExpansionBlockedListControlStatus, sleSecurityAttackExpansionBlockedListControlTimer, sleSecurityAttackExpansionBlockedListControlTimeStamp, sleSecurityAttackExpansionBlockedListControlReqResult, sleSecurityAttackExpansionBlockedListControlRuleIndex, 
				sleSecurityAttackExpansionBlockedListControlBlockTime, sleSecurityAttackBasicBaseDosStatus, sleSecurityAttackBasicBaseScanStatus, sleSecurityAttackBasicBaseCollectInterval, sleSecurityAttackBasicBaseControlDosStatus, 
				sleSecurityAttackBasicBaseControlScanStatus, sleSecurityAttackBasicBaseControlCollectInterval, sleSecurityAttackBasicPolicyAttackType, sleSecurityAttackBasicPolicyThresholdCount, sleSecurityAttackBasicPolicyControlThresholdCount, 
				sleSecurityAttackBasicBlackListIndex, sleSecurityAttackBasicBlackListProtocolType, sleSecurityAttackBasicBlackListSourceIpAddress, sleSecurityAttackBasicBlackListDestinationIpAddress, sleSecurityAttackBasicBlackListBlockingStatus, 
				sleSecurityAttackBasicBlackListControlRequest, sleSecurityAttackBasicBlackListControlStatus, sleSecurityAttackBasicBlackListControlTimer, sleSecurityAttackBasicBlackListControlTimeStamp, sleSecurityAttackBasicBlackListControlReqResult, 
				sleSecurityAttackBasicBlackListControlRuleIndex, sleSecurityAttackBasicBlackListControlProtocolType, sleSecurityAttackBasicBlackListControlSourceIpAddress, sleSecurityLoginLockDelayTime, sleSecurityControlLoginLockDelayTime, 
				sleSecurityAttackBasicBlackListControlDestinationIpAddress, sleSecurityAttackBasicPolicyCollectPorts, sleSecurityAttackBasicPolicyControlCollectPorts, sleSecurityAttackBasicExceptListIngressPort, sleSecurityAttackBasicExceptListControlIngressPort, 
				sleSecurityAttackBasicBlackListIgressPort, sleSecurityAttackBasicBlackListControlIngressPort, sleSecurityAttackBasicBlockedListBlackListIndex, sleSecurityLoginAccountingMode, sleSecurityControlLoginAccountingMode, 
				sleNDInspectLogBufferSize, sleNDInspectLogEntry, sleNDInspectLogInterval, sleNDInspectControlRequest, sleNDInspectControlStatus, 
				sleNDInspectControlTimer, sleNDInspectControlTimeStamp, sleNDInspectControlReqResult, sleNDInspectControlLogBufferSize, sleNDInspectControlLogEntry, 
				sleNDInspectControlLogInterval, sleNDAclIndex, sleNDAclName, sleNDAclNumEntries, sleNDAclControlRequest, 
				sleNDAclControlStatus, sleNDAclControlTimer, sleNDAclControlTimeStamp, sleNDAclControlReqResult, sleNDAclControlIndex, 
				sleNDAclControlName, sleNDAclRuleAclIndex, sleNDAclRuleIndex, sleNDAclRuleAction, sleNDAclRuleType, 
				sleNDAclRuleRangeStartIPv6, sleNDAclRuleRangeEndIPv6, sleNDAclRuleIPv6Address, sleNDAclRuleIPv6Mask, sleNDAclRuleMacAddr, 
				sleNDAclRuleMacType, sleNDAclRuleControlRequest, sleNDAclRuleControlStatus, sleNDAclRuleControlTimer, sleNDAclRuleControlTimeStamp, 
				sleNDAclRuleControlReqResult, sleNDAclRuleControlAclIndex, sleNDAclRuleControlIndex, sleNDAclRuleControlAction, sleNDAclRuleControlType, 
				sleNDAclRuleControlRangeStartIPv6, sleNDAclRuleControlRangeEndIPv6, sleNDAclRuleControlIPv6Address, sleNDAclRuleControlIPv6Mask, sleNDAclRuleControlMacAddr, 
				sleNDAclRuleControlMacType, sleNDInspectVlanIndex, sleNDInspectVlanEnable, sleNDInspectVlanFilterAclIndex, sleNDInspectVlanFwdPktCnt, 
				sleNDInspectVlanDropPktCnt, sleNDInspectVlanAclPermits, sleNDInspectVlanAclDrops, sleNDInspectVlanDhcpv6Permits, sleNDInspectVlanDhcpv6Denys, 
				sleNDInspectVlanLocalIpv6Denys, sleNDInspectVlanFilterAclName, sleNDInspectVlanControlRequest, sleNDInspectVlanControlStatus, sleNDInspectVlanControlTimer, 
				sleNDInspectVlanControlTimeStamp, sleNDInspectVlanControlReqResult, sleNDInspectVlanControlIndex, sleNDInspectVlanControlEnable, sleNDInspectVlanControlFilterAclIndex, 
				sleNDInspectPortIndex, sleNDInspectPortTrust, sleNDInspectPortControlRequest, sleNDInspectPortControlStatus, sleNDInspectPortControlTimer, 
				sleNDInspectPortControlTimeStamp, sleNDInspectPortControlReqResult, sleNDInspectPortControlIndex, sleNDInspectPortControlTrust, sleNDInspectInvalidLogId, 
				sleNDInspectInvalidLogReason, sleNDInspectInvalidLogSamePktCnt, sleNDInspectInvalidLogPortNumber, sleNDInspectInvalidLogVlanId, sleNDInspectInvalidLogSenderMacAddr, 
				sleNDInspectInvalidLogSrcMacAddr, sleNDInspectInvalidLogSenderIpv6Addr, sleNDInspectInvalidLogDstIpv6Addr, sleNDInspectInvalidLogLastRecvTime, sleNDInspectInvalidLogNDType, 
				sleRAGuardPolicyIndex, sleRAGuardPolicyName, sleRAGuardPolicyHoplimitMin, sleRAGuardPolicyHoplimitMax, sleRAGuardPolicyManagedFlag, 
				sleRAGuardPolicyOtherFlag, sleRAGuardPolicyRouterPreference, sleRAGuardPolicyMatchACLName, sleRAGuardPolicyMatchPrefixName, sleRAGuardPolicyControlRequest, 
				sleRAGuardPolicyControlStatus, sleRAGuardPolicyControlTimer, sleRAGuardPolicyControlTimeStamp, sleRAGuardPolicyControlReqResult, sleRAGuardPolicyControlIndex, 
				sleRAGuardPolicyControlName, sleRAGuardPolicyControlHoplimitMin, sleRAGuardPolicyControlHoplimitMax, sleRAGuardPolicyControlManagedFlag, sleRAGuardPolicyControlOtherFlag, 
				sleRAGuardPolicyControlRouterPreference, sleRAGuardPolicyControlMatchACLName, sleRAGuardPolicyControlMatchPrefixName, sleRAGuardVlanIndex, sleRAGuardVlanEnable, 
				sleRAGuardVlanFilterPolicy, sleRAGuardVlanFilterAclName, sleRAGuardVlanControlRequest, sleRAGuardVlanControlStatus, sleRAGuardVlanControlTimer, 
				sleRAGuardVlanControlTimeStamp, sleRAGuardVlanControlReqResult, sleRAGuardVlanControlIndex, sleRAGuardVlanControlEnable, sleRAGuardVlanControlFilterPolicy, 
				sleRAGuardPortIndex, sleRAGuardPortTrust, sleRAGuardPortControlRequest, sleRAGuardPortControlStatus, sleRAGuardPortControlTimer, 
				sleRAGuardPortControlTimeStamp, sleRAGuardPortControlReqResult, sleRAGuardPortControlIndex, sleRAGuardPortControlTrust, sleRadiusServerDot1xAddress, 
				sleRadiusServerDot1xAuthPort, sleRadiusServerDot1xTimeout, sleRadiusServerDot1xRetransmit, sleRadiusServerDot1xClientKey, sleRadiusServerDot1xControlRequest, 
				sleRadiusServerDot1xControlStatus, sleRadiusServerDot1xControlTimer, sleRadiusServerDot1xControlTimeStamp, sleRadiusServerDot1xControlReqResult, sleRadiusServerDot1xControlAddress, 
				sleRadiusServerDot1xControlAuthPort, sleRadiusServerDot1xControlTimeout, sleRadiusServerDot1xControlRetransmit, sleRadiusServerDot1xControlClientKey, sleKeyChainName, 
				sleKeyChainKeyId, sleKeyChainKeyString, sleKeyChainKeyAccepLifeTimeStartTime, sleKeyChainKeyAcceptLifeTimeStartDay, sleKeyChainKeyAcceptLifeTimeStartMonth, 
				sleKeyChainKeyAcceptLifeTimeStartYear, sleKeyChainKeyAcceptLifeTimeExpireType, sleKeyChainKeyAcceptLifeTimeExpireTime, sleKeyChainKeyAcceptLifeTimeExpireDay, sleKeyChainKeyAcceptLifeTimeExpireMonth, 
				sleKeyChainKeyAcceptLifeTimeExpireYear, sleKeyChainKeySendLifeTimeStartTime, sleKeyChainKeySendLifeTimeStartDay, sleKeyChainKeySendLifeTimeStartMonth, sleKeyChainKeySendLifeTimeStartYear, 
				sleKeyChainKeySendLifeTimeExpireType, sleKeyChainKeySendLifeTimeExpireTime, sleKeyChainKeySendLifeTimeExpireDay, sleKeyChainKeySendLifeTimeExpireMonth, sleKeyChainKeySendLifeTimeExpireYear, 
				sleKeyChainControlRequest, sleKeyChainControlStatus, sleKeyChainControlTimer, sleKeyChainControlTimeStamp, sleKeyChainControlReqResult, 
				sleKeyChainControlName, sleKeyChainControlKeyId, sleKeyChainControlKeyString, sleKeyChainControlKeyAcceptLifeTimeStartTime, sleKeyChainControlKeyAcceptLifeTimeStartDay, 
				sleKeyChainControlKeyAcceptLifeTimeStartMonth, sleKeyChainControlKeyAcceptLifeTimeStartYear, sleKeyChainControlKeyAcceptLifeTimeExpireType, sleKeyChainControlKeyAcceptLifeTimeExpireTime, sleKeyChainControlKeyAcceptLifeTimeExpireDay, 
				sleKeyChainControlKeyAcceptLifeTimeExpireMonth, sleKeyChainControlKeyAcceptLifeTimeExpireYear, sleKeyChainControlKeySendLifeTimeStartTime, sleKeyChainControlKeySendLifeTimeStartDay, sleKeyChainControlKeySendLifeTimeStartMonth, 
				sleKeyChainControlKeySendLifeTimeStartYear, sleKeyChainControlKeySendLifeTimeExpireType, sleKeyChainControlKeySendLifeTimeExpireTime, sleKeyChainControlKeySendLifeTimeExpireDay, sleKeyChainControlKeySendLifeTimeExpireMonth, 
				sleKeyChainControlKeySendLifeTimeExpireYear, sleSecurityAttackBasicBlockedListIgressPort, sleSecurityLoginLockAttemptsCount, sleSecurityControlLoginLockAttemptsCount }
			STATUS current
			DESCRIPTION 
				"Description."
			::= { sleSecurity 16 }

		
		sleSecurityNotificationGroup NOTIFICATION-GROUP
			NOTIFICATIONS { sleArpAclCreated, sleArpAclDestroyed, sleArpInspectVlanChanged, sleArpInspectLogBufferSizeChanged, sleArpInspectLogRateChanged, 
				sleSecurityBaseLoginLimitsChanged, sleArpInspectPortChanged, sleSecurityRadiusProfileChanged, sleSecurityTacacsProfileChanged, sleSecurityDot1xActivityChanged, 
				sleAaaProfileChanged, sleRadiusServerCreated, sleRadiusServerDestroyed, sleRadiusServerProfileChanged, sleTacacsServerCreated, 
				sleTacacsServerDestroyed, sleTacacsServerClientKeyChanged, sleAclCreated, sleAclDestroyed, sleAclClassifierProfileChanged, 
				sleAclMatchActionChanged, sleAclNomatchActionChanged, sleDot1xPortProfileChanged, sleDot1xPortAuthSuccessChanged, sleDot1xStatisticsCleared, 
				sleArpInspectValidateChanged, sleArpAclRuleCreated, sleArpAclRuleDestroyed, sleSecurityAttackBasicBaseGlobalStatusChanged, sleSecurityAttackBasicExceptListCreated, 
				sleSecurityAttackBasicExceptListChanged, sleSecurityAttackBasicExceptListDeleted, sleSecurityAttackExpansionBaseGlobalStatusChanged, sleSecurityAttackExpansionPolicyChanged, sleSecurityAttackExpansionExceptListCreated, 
				sleSecurityAttackExpansionExceptListChanged, sleSecurityAttackExpansionExceptListDeleted, sleSecurityAttackExpansionBlockedListBlockTimeChanged, sleSecurityAttackBasicBaseDosStatusChanged, sleSecurityAttackBasicBaseScanStatusChanged, 
				sleSecurityAttackBasicBaseCollectIntervalChanged, sleSecurityAttackBasicPolicyThresholdCountChanged, sleSecurityAttackBasicBlackListDeleted, sleSecurityAttackBasicBlockedListBlockTimeChanged, sleSecurityAttackBasicPolicyBlockTimeChanged, 
				sleSecurityAttackBasicPolicyCollectPortsChanged, sleSecurityBaseLoginLockConfChanged, sleSecurityBaseLoginLockConfDestroyed, sleSecurityLoginAccountingModeChanged, sleNDInspectLogBufferSizeChanged, 
				sleNDInspectLogRateChanged, sleNDAclCreated, sleNDAclDestroyed, sleNDAclRuleCreated, sleNDAclRuleDestroyed, 
				sleNDInspectVlanChanged, sleNDInspectVlanStatsCleared, sleNDInspectPortChanged, sleRAGuardPolicyCreated, sleRAGuardPolicyDestroyed, 
				sleRAGuardPolicyChanged, sleRAGuardVlanChanged, sleRAGuardPortChanged, sleSecurityAttackBasicBlockedListDeleted, sleSecurityAttackBasicBaseAllConfigChanged, 
				setSecurityAttackBasicPolicyAllConfigChanged, sleSecurityAttackBasicBlackListCreated }
			STATUS current
			DESCRIPTION 
				"Description."
			::= { sleSecurity 17 }

		
	
	END

--
-- sle-security-mib.mib
--
