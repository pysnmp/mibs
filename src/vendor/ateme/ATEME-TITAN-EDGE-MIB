ATEME-TITAN-EDGE-MIB DEFINITIONS ::= BEGIN
IMPORTS
    OBJECT-GROUP, MODULE-COMPLIANCE, NOTIFICATION-GROUP
        FROM SNMPv2-CONF
    enterprises, Integer32, OBJECT-TYPE, MODULE-IDENTITY, NOTIFICATION-TYPE
        FROM SNMPv2-SMI
    DisplayString, TruthValue, TEXTUAL-CONVENTION
        FROM SNMPv2-TC
    InetAddressType, InetAddress, InetPortNumber
        FROM INET-ADDRESS-MIB;

ateme MODULE-IDENTITY
    LAST-UPDATED "202212141334Z"
    ORGANIZATION "ATEME"
    CONTACT-INFO "support@ateme.com"
    DESCRIPTION "2.11.1 - Copyright (C) ATEME (2011-2019)"
    ::= { enterprises 27338 }

titanEdge OBJECT IDENTIFIER ::= { ateme 50 }

titanEdgeNotifications OBJECT IDENTIFIER ::= { titanEdge 2 }

titanEdgeConformance OBJECT IDENTIFIER ::= { titanEdge 1 }

titanEdgeGateway OBJECT IDENTIFIER ::= { titanEdgeNotifications 4 }

titanEdgeEncoder OBJECT IDENTIFIER ::= { titanEdgeNotifications 3 }

titanEdgeDecoder OBJECT IDENTIFIER ::= { titanEdgeNotifications 2 }

titanEdgeAppliance OBJECT IDENTIFIER ::= { titanEdgeNotifications 1 }

titanEdgeCompliances OBJECT IDENTIFIER ::= { titanEdgeConformance 2 }

titanEdgeGroups OBJECT IDENTIFIER ::= { titanEdgeConformance 1 }

titanEdgeGatewayProcessing OBJECT IDENTIFIER ::= { titanEdgeGateway 3 }

titanEdgeGatewayScheduler OBJECT IDENTIFIER ::= { titanEdgeGateway 2 }

titanEdgeGatewayApi OBJECT IDENTIFIER ::= { titanEdgeGateway 1 }

titanEdgeEncoderProcessing OBJECT IDENTIFIER ::= { titanEdgeEncoder 3 }

titanEdgeEncoderScheduler OBJECT IDENTIFIER ::= { titanEdgeEncoder 2 }

titanEdgeEncoderApi OBJECT IDENTIFIER ::= { titanEdgeEncoder 1 }

titanEdgeDecoderProcessing OBJECT IDENTIFIER ::= { titanEdgeDecoder 3 }

titanEdgeDecoderScheduler OBJECT IDENTIFIER ::= { titanEdgeDecoder 2 }

titanEdgeDecoderApi OBJECT IDENTIFIER ::= { titanEdgeDecoder 1 }

titanEdgeApplianceMonitor OBJECT IDENTIFIER ::= { titanEdgeAppliance 2 }

titanEdgeApplianceApi OBJECT IDENTIFIER ::= { titanEdgeAppliance 1 }

titanEdgeGatewayProcessingAlarms OBJECT IDENTIFIER ::= { titanEdgeGatewayProcessing 2 }

titanEdgeGatewayProcessingLogProcessingFailure OBJECT IDENTIFIER ::= { titanEdgeGatewayProcessing 1 }

titanEdgeGatewayProcessingLogs OBJECT IDENTIFIER ::= { titanEdgeGatewayProcessing 1 }

titanEdgeGatewaySchedulerAlarmCompositionMCamDuplicatedPrograms OBJECT IDENTIFIER ::= { titanEdgeGatewayScheduler 2 }

titanEdgeGatewaySchedulerAlarmCompositionMCamHardwareError OBJECT IDENTIFIER ::= { titanEdgeGatewayScheduler 2 }

titanEdgeGatewaySchedulerAlarmCompositionMCamLimitsReached OBJECT IDENTIFIER ::= { titanEdgeGatewayScheduler 2 }

titanEdgeGatewaySchedulerAlarmTsNoOutputConnection OBJECT IDENTIFIER ::= { titanEdgeGatewayScheduler 2 }

titanEdgeGatewaySchedulerAlarmOutputBitrateInvalid OBJECT IDENTIFIER ::= { titanEdgeGatewayScheduler 2 }

titanEdgeGatewaySchedulerAlarmOutputDiscardedPackets OBJECT IDENTIFIER ::= { titanEdgeGatewayScheduler 2 }

titanEdgeGatewaySchedulerAlarmCompositionRemuxLimitsReached OBJECT IDENTIFIER ::= { titanEdgeGatewayScheduler 2 }

titanEdgeGatewaySchedulerAlarmCompositionRemuxRemappingDetected OBJECT IDENTIFIER ::= { titanEdgeGatewayScheduler 2 }

titanEdgeGatewaySchedulerAlarmCompositionRemuxInputsMissingActivity OBJECT IDENTIFIER ::= { titanEdgeGatewayScheduler 2 }

titanEdgeGatewaySchedulerAlarmCompositionProgramDescramblingPrevented OBJECT IDENTIFIER ::= { titanEdgeGatewayScheduler 2 }

titanEdgeGatewaySchedulerAlarmSystemExtensionPinConfigurationInvalid OBJECT IDENTIFIER ::= { titanEdgeGatewayScheduler 2 }

titanEdgeGatewaySchedulerAlarmSystemExtensionPinInConflict OBJECT IDENTIFIER ::= { titanEdgeGatewayScheduler 2 }

titanEdgeGatewaySchedulerAlarmSystemExtensionPinUnknown OBJECT IDENTIFIER ::= { titanEdgeGatewayScheduler 2 }

titanEdgeGatewaySchedulerAlarmSystemEthernetUnknown OBJECT IDENTIFIER ::= { titanEdgeGatewayScheduler 2 }

titanEdgeGatewaySchedulerAlarmChannelLost OBJECT IDENTIFIER ::= { titanEdgeGatewayScheduler 2 }

titanEdgeGatewaySchedulerAlarmLicenseMissing OBJECT IDENTIFIER ::= { titanEdgeGatewayScheduler 2 }

titanEdgeGatewaySchedulerAlarmTsSmpte20227SkewTooLarge OBJECT IDENTIFIER ::= { titanEdgeGatewayScheduler 2 }

titanEdgeGatewaySchedulerAlarmTsSmpte20227SignalMissing OBJECT IDENTIFIER ::= { titanEdgeGatewayScheduler 2 }

titanEdgeGatewaySchedulerAlarmInternalInputNotConnected OBJECT IDENTIFIER ::= { titanEdgeGatewayScheduler 2 }

titanEdgeGatewaySchedulerAlarmZixiExcessiveJitter OBJECT IDENTIFIER ::= { titanEdgeGatewayScheduler 2 }

titanEdgeGatewaySchedulerAlarmZixiInputNotConnected OBJECT IDENTIFIER ::= { titanEdgeGatewayScheduler 2 }

titanEdgeGatewaySchedulerAlarmSatelliteInputSignalNotLocked OBJECT IDENTIFIER ::= { titanEdgeGatewayScheduler 2 }

titanEdgeGatewaySchedulerAlarmTsInputSignalMissing OBJECT IDENTIFIER ::= { titanEdgeGatewayScheduler 2 }

titanEdgeGatewaySchedulerAlarmChannelInternalError OBJECT IDENTIFIER ::= { titanEdgeGatewayScheduler 2 }

titanEdgeGatewaySchedulerAlarms OBJECT IDENTIFIER ::= { titanEdgeGatewayScheduler 2 }

titanEdgeGatewaySchedulerLogChannelFailoverInputChanged OBJECT IDENTIFIER ::= { titanEdgeGatewayScheduler 1 }

titanEdgeGatewaySchedulerLogChannelStopped OBJECT IDENTIFIER ::= { titanEdgeGatewayScheduler 1 }

titanEdgeGatewaySchedulerLogChannelStarted OBJECT IDENTIFIER ::= { titanEdgeGatewayScheduler 1 }

titanEdgeGatewaySchedulerLogs OBJECT IDENTIFIER ::= { titanEdgeGatewayScheduler 1 }

titanEdgeGatewayApiAlarms OBJECT IDENTIFIER ::= { titanEdgeGatewayApi 2 }

titanEdgeGatewayApiLogChannelModified OBJECT IDENTIFIER ::= { titanEdgeGatewayApi 1 }

titanEdgeGatewayApiLogChannelDeleted OBJECT IDENTIFIER ::= { titanEdgeGatewayApi 1 }

titanEdgeGatewayApiLogChannelAdded OBJECT IDENTIFIER ::= { titanEdgeGatewayApi 1 }

titanEdgeGatewayApiLogs OBJECT IDENTIFIER ::= { titanEdgeGatewayApi 1 }

titanEdgeEncoderProcessingAlarms OBJECT IDENTIFIER ::= { titanEdgeEncoderProcessing 2 }

titanEdgeEncoderProcessingLogProcessingFailure OBJECT IDENTIFIER ::= { titanEdgeEncoderProcessing 1 }

titanEdgeEncoderProcessingLogs OBJECT IDENTIFIER ::= { titanEdgeEncoderProcessing 1 }

titanEdgeEncoderSchedulerAlarmTsNoOutputConnection OBJECT IDENTIFIER ::= { titanEdgeEncoderScheduler 2 }

titanEdgeEncoderSchedulerAlarmSystemRivermaxLicenseIssue OBJECT IDENTIFIER ::= { titanEdgeEncoderScheduler 2 }

titanEdgeEncoderSchedulerAlarmSystemExtensionPinConfigurationInvalid OBJECT IDENTIFIER ::= { titanEdgeEncoderScheduler 2 }

titanEdgeEncoderSchedulerAlarmSystemExtensionPinInConflict OBJECT IDENTIFIER ::= { titanEdgeEncoderScheduler 2 }

titanEdgeEncoderSchedulerAlarmSystemExtensionPinUnknown OBJECT IDENTIFIER ::= { titanEdgeEncoderScheduler 2 }

titanEdgeEncoderSchedulerAlarmSystemEthernetUnknown OBJECT IDENTIFIER ::= { titanEdgeEncoderScheduler 2 }

titanEdgeEncoderSchedulerAlarmOutputBitrateInvalid OBJECT IDENTIFIER ::= { titanEdgeEncoderScheduler 2 }

titanEdgeEncoderSchedulerAlarmOutputDiscardedPackets OBJECT IDENTIFIER ::= { titanEdgeEncoderScheduler 2 }

titanEdgeEncoderSchedulerAlarmCompositionAudioSourceInactive OBJECT IDENTIFIER ::= { titanEdgeEncoderScheduler 2 }

titanEdgeEncoderSchedulerAlarmCompositionAudioSourceIncompatible OBJECT IDENTIFIER ::= { titanEdgeEncoderScheduler 2 }

titanEdgeEncoderSchedulerAlarmCompositionAudioSourceMissing OBJECT IDENTIFIER ::= { titanEdgeEncoderScheduler 2 }

titanEdgeEncoderSchedulerAlarmCompositionVideoSourceIncompatible OBJECT IDENTIFIER ::= { titanEdgeEncoderScheduler 2 }

titanEdgeEncoderSchedulerAlarmCompositionVideoSourceNotSupported OBJECT IDENTIFIER ::= { titanEdgeEncoderScheduler 2 }

titanEdgeEncoderSchedulerAlarmCompositionVideoSourceMissing OBJECT IDENTIFIER ::= { titanEdgeEncoderScheduler 2 }

titanEdgeEncoderSchedulerAlarmTsOccupancyBitrateInvalid OBJECT IDENTIFIER ::= { titanEdgeEncoderScheduler 2 }

titanEdgeEncoderSchedulerAlarmTsOutputBitrateDifferent OBJECT IDENTIFIER ::= { titanEdgeEncoderScheduler 2 }

titanEdgeEncoderSchedulerAlarmChannelLost OBJECT IDENTIFIER ::= { titanEdgeEncoderScheduler 2 }

titanEdgeEncoderSchedulerAlarmLicenseMissing OBJECT IDENTIFIER ::= { titanEdgeEncoderScheduler 2 }

titanEdgeEncoderSchedulerAlarmChannelInternalError OBJECT IDENTIFIER ::= { titanEdgeEncoderScheduler 2 }

titanEdgeEncoderSchedulerAlarms OBJECT IDENTIFIER ::= { titanEdgeEncoderScheduler 2 }

titanEdgeEncoderSchedulerLogChannelFailoverInputChanged OBJECT IDENTIFIER ::= { titanEdgeEncoderScheduler 1 }

titanEdgeEncoderSchedulerLogChannelStopped OBJECT IDENTIFIER ::= { titanEdgeEncoderScheduler 1 }

titanEdgeEncoderSchedulerLogChannelStarted OBJECT IDENTIFIER ::= { titanEdgeEncoderScheduler 1 }

titanEdgeEncoderSchedulerLogs OBJECT IDENTIFIER ::= { titanEdgeEncoderScheduler 1 }

titanEdgeEncoderApiAlarms OBJECT IDENTIFIER ::= { titanEdgeEncoderApi 2 }

titanEdgeEncoderApiLogChannelModified OBJECT IDENTIFIER ::= { titanEdgeEncoderApi 1 }

titanEdgeEncoderApiLogChannelDeleted OBJECT IDENTIFIER ::= { titanEdgeEncoderApi 1 }

titanEdgeEncoderApiLogChannelAdded OBJECT IDENTIFIER ::= { titanEdgeEncoderApi 1 }

titanEdgeEncoderApiLogs OBJECT IDENTIFIER ::= { titanEdgeEncoderApi 1 }

titanEdgeDecoderProcessingAlarms OBJECT IDENTIFIER ::= { titanEdgeDecoderProcessing 2 }

titanEdgeDecoderProcessingLogProcessingFailure OBJECT IDENTIFIER ::= { titanEdgeDecoderProcessing 1 }

titanEdgeDecoderProcessingLogs OBJECT IDENTIFIER ::= { titanEdgeDecoderProcessing 1 }

titanEdgeDecoderSchedulerAlarmCompositionMCamDuplicatedPrograms OBJECT IDENTIFIER ::= { titanEdgeDecoderScheduler 2 }

titanEdgeDecoderSchedulerAlarmCompositionMCamHardwareError OBJECT IDENTIFIER ::= { titanEdgeDecoderScheduler 2 }

titanEdgeDecoderSchedulerAlarmCompositionMCamLimitsReached OBJECT IDENTIFIER ::= { titanEdgeDecoderScheduler 2 }

titanEdgeDecoderSchedulerAlarm2110Smpte20227ConfigurationInvalid OBJECT IDENTIFIER ::= { titanEdgeDecoderScheduler 2 }

titanEdgeDecoderSchedulerAlarmSystemRivermaxLicenseIssue OBJECT IDENTIFIER ::= { titanEdgeDecoderScheduler 2 }

titanEdgeDecoderSchedulerAlarmSystemExtensionPinConfigurationInvalid OBJECT IDENTIFIER ::= { titanEdgeDecoderScheduler 2 }

titanEdgeDecoderSchedulerAlarmSystemExtensionPinInConflict OBJECT IDENTIFIER ::= { titanEdgeDecoderScheduler 2 }

titanEdgeDecoderSchedulerAlarmSystemExtensionPinUnknown OBJECT IDENTIFIER ::= { titanEdgeDecoderScheduler 2 }

titanEdgeDecoderSchedulerAlarmSystemEthernetUnknown OBJECT IDENTIFIER ::= { titanEdgeDecoderScheduler 2 }

titanEdgeDecoderSchedulerAlarmSdiOutputGenlockUnlocked OBJECT IDENTIFIER ::= { titanEdgeDecoderScheduler 2 }

titanEdgeDecoderSchedulerAlarmSdiOutputInvalidTimecodeOffset OBJECT IDENTIFIER ::= { titanEdgeDecoderScheduler 2 }

titanEdgeDecoderSchedulerAlarmCompositionWatermarkingNotAvailable OBJECT IDENTIFIER ::= { titanEdgeDecoderScheduler 2 }

titanEdgeDecoderSchedulerAlarmCompositionVideoConstraintIncompatible OBJECT IDENTIFIER ::= { titanEdgeDecoderScheduler 2 }

titanEdgeDecoderSchedulerAlarmCompositionDataSourceMissing OBJECT IDENTIFIER ::= { titanEdgeDecoderScheduler 2 }

titanEdgeDecoderSchedulerAlarmCompositionAudioSourceMissing OBJECT IDENTIFIER ::= { titanEdgeDecoderScheduler 2 }

titanEdgeDecoderSchedulerAlarmCompositionVideoSourceMissing OBJECT IDENTIFIER ::= { titanEdgeDecoderScheduler 2 }

titanEdgeDecoderSchedulerAlarmCompositionProgramDecodingPrevented OBJECT IDENTIFIER ::= { titanEdgeDecoderScheduler 2 }

titanEdgeDecoderSchedulerAlarmCompositionProgramScrambled OBJECT IDENTIFIER ::= { titanEdgeDecoderScheduler 2 }

titanEdgeDecoderSchedulerAlarmCompositionProgramMissing OBJECT IDENTIFIER ::= { titanEdgeDecoderScheduler 2 }

titanEdgeDecoderSchedulerAlarmChannelLost OBJECT IDENTIFIER ::= { titanEdgeDecoderScheduler 2 }

titanEdgeDecoderSchedulerAlarmLicenseMissing OBJECT IDENTIFIER ::= { titanEdgeDecoderScheduler 2 }

titanEdgeDecoderSchedulerAlarmTsSmpte20227SkewTooLarge OBJECT IDENTIFIER ::= { titanEdgeDecoderScheduler 2 }

titanEdgeDecoderSchedulerAlarmTsSmpte20227SignalMissing OBJECT IDENTIFIER ::= { titanEdgeDecoderScheduler 2 }

titanEdgeDecoderSchedulerAlarmInternalInputNotConnected OBJECT IDENTIFIER ::= { titanEdgeDecoderScheduler 2 }

titanEdgeDecoderSchedulerAlarmZixiExcessiveJitter OBJECT IDENTIFIER ::= { titanEdgeDecoderScheduler 2 }

titanEdgeDecoderSchedulerAlarmZixiInputNotConnected OBJECT IDENTIFIER ::= { titanEdgeDecoderScheduler 2 }

titanEdgeDecoderSchedulerAlarmSatelliteInputSignalNotLocked OBJECT IDENTIFIER ::= { titanEdgeDecoderScheduler 2 }

titanEdgeDecoderSchedulerAlarmTsInputSignalMissing OBJECT IDENTIFIER ::= { titanEdgeDecoderScheduler 2 }

titanEdgeDecoderSchedulerAlarmChannelInternalError OBJECT IDENTIFIER ::= { titanEdgeDecoderScheduler 2 }

titanEdgeDecoderSchedulerAlarms OBJECT IDENTIFIER ::= { titanEdgeDecoderScheduler 2 }

titanEdgeDecoderSchedulerLogOutputSplicingDone OBJECT IDENTIFIER ::= { titanEdgeDecoderScheduler 1 }

titanEdgeDecoderSchedulerLogOutputSplicingInProgress OBJECT IDENTIFIER ::= { titanEdgeDecoderScheduler 1 }

titanEdgeDecoderSchedulerLogChannelFailoverInputChanged OBJECT IDENTIFIER ::= { titanEdgeDecoderScheduler 1 }

titanEdgeDecoderSchedulerLogChannelStopped OBJECT IDENTIFIER ::= { titanEdgeDecoderScheduler 1 }

titanEdgeDecoderSchedulerLogChannelStarted OBJECT IDENTIFIER ::= { titanEdgeDecoderScheduler 1 }

titanEdgeDecoderSchedulerLogs OBJECT IDENTIFIER ::= { titanEdgeDecoderScheduler 1 }

titanEdgeDecoderApiAlarms OBJECT IDENTIFIER ::= { titanEdgeDecoderApi 2 }

titanEdgeDecoderApiLogChannelModified OBJECT IDENTIFIER ::= { titanEdgeDecoderApi 1 }

titanEdgeDecoderApiLogChannelDeleted OBJECT IDENTIFIER ::= { titanEdgeDecoderApi 1 }

titanEdgeDecoderApiLogChannelAdded OBJECT IDENTIFIER ::= { titanEdgeDecoderApi 1 }

titanEdgeDecoderApiLogs OBJECT IDENTIFIER ::= { titanEdgeDecoderApi 1 }

titanEdgeApplianceMonitorAlarmSystemPsuFailure OBJECT IDENTIFIER ::= { titanEdgeApplianceMonitor 2 }

titanEdgeApplianceMonitorAlarmSystemEthernetLinkDown OBJECT IDENTIFIER ::= { titanEdgeApplianceMonitor 2 }

titanEdgeApplianceMonitorAlarms OBJECT IDENTIFIER ::= { titanEdgeApplianceMonitor 2 }

titanEdgeApplianceMonitorLogDvbSsuAssetDeleted OBJECT IDENTIFIER ::= { titanEdgeApplianceMonitor 1 }

titanEdgeApplianceMonitorLogDvbSsuAssetUpdate OBJECT IDENTIFIER ::= { titanEdgeApplianceMonitor 1 }

titanEdgeApplianceMonitorLogDvbSsuFirmwareUpdateRejected OBJECT IDENTIFIER ::= { titanEdgeApplianceMonitor 1 }

titanEdgeApplianceMonitorLogDvbSsuFirmwareUpdating OBJECT IDENTIFIER ::= { titanEdgeApplianceMonitor 1 }

titanEdgeApplianceMonitorLogDvbSsuLicenseUpdate OBJECT IDENTIFIER ::= { titanEdgeApplianceMonitor 1 }

titanEdgeApplianceMonitorLogDvbSsuChannelUpdate OBJECT IDENTIFIER ::= { titanEdgeApplianceMonitor 1 }

titanEdgeApplianceMonitorLogSystemEthernetIgmpVersionChanged OBJECT IDENTIFIER ::= { titanEdgeApplianceMonitor 1 }

titanEdgeApplianceMonitorLogSystemStopped OBJECT IDENTIFIER ::= { titanEdgeApplianceMonitor 1 }

titanEdgeApplianceMonitorLogSystemStarted OBJECT IDENTIFIER ::= { titanEdgeApplianceMonitor 1 }

titanEdgeApplianceMonitorLogs OBJECT IDENTIFIER ::= { titanEdgeApplianceMonitor 1 }

titanEdgeApplianceApiAlarms OBJECT IDENTIFIER ::= { titanEdgeApplianceApi 2 }

titanEdgeApplianceApiLogs OBJECT IDENTIFIER ::= { titanEdgeApplianceApi 1 }

titanEdgeGatewaySchedulerAlarmCompositionMCamDuplicatedProgramsOff OBJECT IDENTIFIER ::= { titanEdgeGatewaySchedulerAlarms 44 }

titanEdgeGatewaySchedulerAlarmCompositionMCamDuplicatedProgramsOn OBJECT IDENTIFIER ::= { titanEdgeGatewaySchedulerAlarms 44 }

titanEdgeGatewaySchedulerAlarmCompositionMCamHardwareErrorOff OBJECT IDENTIFIER ::= { titanEdgeGatewaySchedulerAlarms 42 }

titanEdgeGatewaySchedulerAlarmCompositionMCamHardwareErrorOn OBJECT IDENTIFIER ::= { titanEdgeGatewaySchedulerAlarms 42 }

titanEdgeGatewaySchedulerAlarmCompositionMCamLimitsReachedOff OBJECT IDENTIFIER ::= { titanEdgeGatewaySchedulerAlarms 41 }

titanEdgeGatewaySchedulerAlarmCompositionMCamLimitsReachedOn OBJECT IDENTIFIER ::= { titanEdgeGatewaySchedulerAlarms 41 }

titanEdgeGatewaySchedulerAlarmTsNoOutputConnectionOff OBJECT IDENTIFIER ::= { titanEdgeGatewaySchedulerAlarms 40 }

titanEdgeGatewaySchedulerAlarmTsNoOutputConnectionOn OBJECT IDENTIFIER ::= { titanEdgeGatewaySchedulerAlarms 40 }

titanEdgeGatewaySchedulerAlarmOutputBitrateInvalidOff OBJECT IDENTIFIER ::= { titanEdgeGatewaySchedulerAlarms 43 }

titanEdgeGatewaySchedulerAlarmOutputBitrateInvalidOn OBJECT IDENTIFIER ::= { titanEdgeGatewaySchedulerAlarms 43 }

titanEdgeGatewaySchedulerAlarmOutputDiscardedPacketsOff OBJECT IDENTIFIER ::= { titanEdgeGatewaySchedulerAlarms 35 }

titanEdgeGatewaySchedulerAlarmOutputDiscardedPacketsOn OBJECT IDENTIFIER ::= { titanEdgeGatewaySchedulerAlarms 35 }

titanEdgeGatewaySchedulerAlarmCompositionRemuxLimitsReachedOff OBJECT IDENTIFIER ::= { titanEdgeGatewaySchedulerAlarms 39 }

titanEdgeGatewaySchedulerAlarmCompositionRemuxLimitsReachedOn OBJECT IDENTIFIER ::= { titanEdgeGatewaySchedulerAlarms 39 }

titanEdgeGatewaySchedulerAlarmCompositionRemuxRemappingDetectedOff OBJECT IDENTIFIER ::= { titanEdgeGatewaySchedulerAlarms 37 }

titanEdgeGatewaySchedulerAlarmCompositionRemuxRemappingDetectedOn OBJECT IDENTIFIER ::= { titanEdgeGatewaySchedulerAlarms 37 }

titanEdgeGatewaySchedulerAlarmCompositionRemuxInputsMissingActivityOff OBJECT IDENTIFIER ::= { titanEdgeGatewaySchedulerAlarms 38 }

titanEdgeGatewaySchedulerAlarmCompositionRemuxInputsMissingActivityOn OBJECT IDENTIFIER ::= { titanEdgeGatewaySchedulerAlarms 38 }

titanEdgeGatewaySchedulerAlarmCompositionProgramDescramblingPreventedOff OBJECT IDENTIFIER ::= { titanEdgeGatewaySchedulerAlarms 31 }

titanEdgeGatewaySchedulerAlarmCompositionProgramDescramblingPreventedOn OBJECT IDENTIFIER ::= { titanEdgeGatewaySchedulerAlarms 31 }

titanEdgeGatewaySchedulerAlarmSystemExtensionPinConfigurationInvalidOff OBJECT IDENTIFIER ::= { titanEdgeGatewaySchedulerAlarms 24 }

titanEdgeGatewaySchedulerAlarmSystemExtensionPinConfigurationInvalidOn OBJECT IDENTIFIER ::= { titanEdgeGatewaySchedulerAlarms 24 }

titanEdgeGatewaySchedulerAlarmSystemExtensionPinInConflictOff OBJECT IDENTIFIER ::= { titanEdgeGatewaySchedulerAlarms 23 }

titanEdgeGatewaySchedulerAlarmSystemExtensionPinInConflictOn OBJECT IDENTIFIER ::= { titanEdgeGatewaySchedulerAlarms 23 }

titanEdgeGatewaySchedulerAlarmSystemExtensionPinUnknownOff OBJECT IDENTIFIER ::= { titanEdgeGatewaySchedulerAlarms 21 }

titanEdgeGatewaySchedulerAlarmSystemExtensionPinUnknownOn OBJECT IDENTIFIER ::= { titanEdgeGatewaySchedulerAlarms 21 }

titanEdgeGatewaySchedulerAlarmSystemEthernetUnknownOff OBJECT IDENTIFIER ::= { titanEdgeGatewaySchedulerAlarms 30 }

titanEdgeGatewaySchedulerAlarmSystemEthernetUnknownOn OBJECT IDENTIFIER ::= { titanEdgeGatewaySchedulerAlarms 30 }

titanEdgeGatewaySchedulerAlarmChannelLostOff OBJECT IDENTIFIER ::= { titanEdgeGatewaySchedulerAlarms 33 }

titanEdgeGatewaySchedulerAlarmChannelLostOn OBJECT IDENTIFIER ::= { titanEdgeGatewaySchedulerAlarms 33 }

titanEdgeGatewaySchedulerAlarmLicenseMissingOff OBJECT IDENTIFIER ::= { titanEdgeGatewaySchedulerAlarms 11 }

titanEdgeGatewaySchedulerAlarmLicenseMissingOn OBJECT IDENTIFIER ::= { titanEdgeGatewaySchedulerAlarms 11 }

titanEdgeGatewaySchedulerAlarmTsSmpte20227SkewTooLargeOff OBJECT IDENTIFIER ::= { titanEdgeGatewaySchedulerAlarms 29 }

titanEdgeGatewaySchedulerAlarmTsSmpte20227SkewTooLargeOn OBJECT IDENTIFIER ::= { titanEdgeGatewaySchedulerAlarms 29 }

titanEdgeGatewaySchedulerAlarmTsSmpte20227SignalMissingOff OBJECT IDENTIFIER ::= { titanEdgeGatewaySchedulerAlarms 28 }

titanEdgeGatewaySchedulerAlarmTsSmpte20227SignalMissingOn OBJECT IDENTIFIER ::= { titanEdgeGatewaySchedulerAlarms 28 }

titanEdgeGatewaySchedulerAlarmInternalInputNotConnectedOff OBJECT IDENTIFIER ::= { titanEdgeGatewaySchedulerAlarms 25 }

titanEdgeGatewaySchedulerAlarmInternalInputNotConnectedOn OBJECT IDENTIFIER ::= { titanEdgeGatewaySchedulerAlarms 25 }

titanEdgeGatewaySchedulerAlarmZixiExcessiveJitterOff OBJECT IDENTIFIER ::= { titanEdgeGatewaySchedulerAlarms 5 }

titanEdgeGatewaySchedulerAlarmZixiExcessiveJitterOn OBJECT IDENTIFIER ::= { titanEdgeGatewaySchedulerAlarms 5 }

titanEdgeGatewaySchedulerAlarmZixiInputNotConnectedOff OBJECT IDENTIFIER ::= { titanEdgeGatewaySchedulerAlarms 4 }

titanEdgeGatewaySchedulerAlarmZixiInputNotConnectedOn OBJECT IDENTIFIER ::= { titanEdgeGatewaySchedulerAlarms 4 }

titanEdgeGatewaySchedulerAlarmSatelliteInputSignalNotLockedOff OBJECT IDENTIFIER ::= { titanEdgeGatewaySchedulerAlarms 3 }

titanEdgeGatewaySchedulerAlarmSatelliteInputSignalNotLockedOn OBJECT IDENTIFIER ::= { titanEdgeGatewaySchedulerAlarms 3 }

titanEdgeGatewaySchedulerAlarmTsInputSignalMissingOff OBJECT IDENTIFIER ::= { titanEdgeGatewaySchedulerAlarms 2 }

titanEdgeGatewaySchedulerAlarmTsInputSignalMissingOn OBJECT IDENTIFIER ::= { titanEdgeGatewaySchedulerAlarms 2 }

titanEdgeGatewaySchedulerAlarmChannelInternalErrorOff OBJECT IDENTIFIER ::= { titanEdgeGatewaySchedulerAlarms 19 }

titanEdgeGatewaySchedulerAlarmChannelInternalErrorOn OBJECT IDENTIFIER ::= { titanEdgeGatewaySchedulerAlarms 19 }

titanEdgeEncoderSchedulerAlarmTsNoOutputConnectionOff OBJECT IDENTIFIER ::= { titanEdgeEncoderSchedulerAlarms 40 }

titanEdgeEncoderSchedulerAlarmTsNoOutputConnectionOn OBJECT IDENTIFIER ::= { titanEdgeEncoderSchedulerAlarms 40 }

titanEdgeEncoderSchedulerAlarmSystemRivermaxLicenseIssueOff OBJECT IDENTIFIER ::= { titanEdgeEncoderSchedulerAlarms 26 }

titanEdgeEncoderSchedulerAlarmSystemRivermaxLicenseIssueOn OBJECT IDENTIFIER ::= { titanEdgeEncoderSchedulerAlarms 26 }

titanEdgeEncoderSchedulerAlarmSystemExtensionPinConfigurationInvalidOff OBJECT IDENTIFIER ::= { titanEdgeEncoderSchedulerAlarms 24 }

titanEdgeEncoderSchedulerAlarmSystemExtensionPinConfigurationInvalidOn OBJECT IDENTIFIER ::= { titanEdgeEncoderSchedulerAlarms 24 }

titanEdgeEncoderSchedulerAlarmSystemExtensionPinInConflictOff OBJECT IDENTIFIER ::= { titanEdgeEncoderSchedulerAlarms 23 }

titanEdgeEncoderSchedulerAlarmSystemExtensionPinInConflictOn OBJECT IDENTIFIER ::= { titanEdgeEncoderSchedulerAlarms 23 }

titanEdgeEncoderSchedulerAlarmSystemExtensionPinUnknownOff OBJECT IDENTIFIER ::= { titanEdgeEncoderSchedulerAlarms 21 }

titanEdgeEncoderSchedulerAlarmSystemExtensionPinUnknownOn OBJECT IDENTIFIER ::= { titanEdgeEncoderSchedulerAlarms 21 }

titanEdgeEncoderSchedulerAlarmSystemEthernetUnknownOff OBJECT IDENTIFIER ::= { titanEdgeEncoderSchedulerAlarms 30 }

titanEdgeEncoderSchedulerAlarmSystemEthernetUnknownOn OBJECT IDENTIFIER ::= { titanEdgeEncoderSchedulerAlarms 30 }

titanEdgeEncoderSchedulerAlarmOutputBitrateInvalidOff OBJECT IDENTIFIER ::= { titanEdgeEncoderSchedulerAlarms 43 }

titanEdgeEncoderSchedulerAlarmOutputBitrateInvalidOn OBJECT IDENTIFIER ::= { titanEdgeEncoderSchedulerAlarms 43 }

titanEdgeEncoderSchedulerAlarmOutputDiscardedPacketsOff OBJECT IDENTIFIER ::= { titanEdgeEncoderSchedulerAlarms 35 }

titanEdgeEncoderSchedulerAlarmOutputDiscardedPacketsOn OBJECT IDENTIFIER ::= { titanEdgeEncoderSchedulerAlarms 35 }

titanEdgeEncoderSchedulerAlarmCompositionAudioSourceInactiveOff OBJECT IDENTIFIER ::= { titanEdgeEncoderSchedulerAlarms 16 }

titanEdgeEncoderSchedulerAlarmCompositionAudioSourceInactiveOn OBJECT IDENTIFIER ::= { titanEdgeEncoderSchedulerAlarms 16 }

titanEdgeEncoderSchedulerAlarmCompositionAudioSourceIncompatibleOff OBJECT IDENTIFIER ::= { titanEdgeEncoderSchedulerAlarms 15 }

titanEdgeEncoderSchedulerAlarmCompositionAudioSourceIncompatibleOn OBJECT IDENTIFIER ::= { titanEdgeEncoderSchedulerAlarms 15 }

titanEdgeEncoderSchedulerAlarmCompositionAudioSourceMissingOff OBJECT IDENTIFIER ::= { titanEdgeEncoderSchedulerAlarms 9 }

titanEdgeEncoderSchedulerAlarmCompositionAudioSourceMissingOn OBJECT IDENTIFIER ::= { titanEdgeEncoderSchedulerAlarms 9 }

titanEdgeEncoderSchedulerAlarmCompositionVideoSourceIncompatibleOff OBJECT IDENTIFIER ::= { titanEdgeEncoderSchedulerAlarms 13 }

titanEdgeEncoderSchedulerAlarmCompositionVideoSourceIncompatibleOn OBJECT IDENTIFIER ::= { titanEdgeEncoderSchedulerAlarms 13 }

titanEdgeEncoderSchedulerAlarmCompositionVideoSourceNotSupportedOff OBJECT IDENTIFIER ::= { titanEdgeEncoderSchedulerAlarms 14 }

titanEdgeEncoderSchedulerAlarmCompositionVideoSourceNotSupportedOn OBJECT IDENTIFIER ::= { titanEdgeEncoderSchedulerAlarms 14 }

titanEdgeEncoderSchedulerAlarmCompositionVideoSourceMissingOff OBJECT IDENTIFIER ::= { titanEdgeEncoderSchedulerAlarms 8 }

titanEdgeEncoderSchedulerAlarmCompositionVideoSourceMissingOn OBJECT IDENTIFIER ::= { titanEdgeEncoderSchedulerAlarms 8 }

titanEdgeEncoderSchedulerAlarmTsOccupancyBitrateInvalidOff OBJECT IDENTIFIER ::= { titanEdgeEncoderSchedulerAlarms 27 }

titanEdgeEncoderSchedulerAlarmTsOccupancyBitrateInvalidOn OBJECT IDENTIFIER ::= { titanEdgeEncoderSchedulerAlarms 27 }

titanEdgeEncoderSchedulerAlarmTsOutputBitrateDifferentOff OBJECT IDENTIFIER ::= { titanEdgeEncoderSchedulerAlarms 17 }

titanEdgeEncoderSchedulerAlarmTsOutputBitrateDifferentOn OBJECT IDENTIFIER ::= { titanEdgeEncoderSchedulerAlarms 17 }

titanEdgeEncoderSchedulerAlarmChannelLostOff OBJECT IDENTIFIER ::= { titanEdgeEncoderSchedulerAlarms 33 }

titanEdgeEncoderSchedulerAlarmChannelLostOn OBJECT IDENTIFIER ::= { titanEdgeEncoderSchedulerAlarms 33 }

titanEdgeEncoderSchedulerAlarmLicenseMissingOff OBJECT IDENTIFIER ::= { titanEdgeEncoderSchedulerAlarms 11 }

titanEdgeEncoderSchedulerAlarmLicenseMissingOn OBJECT IDENTIFIER ::= { titanEdgeEncoderSchedulerAlarms 11 }

titanEdgeEncoderSchedulerAlarmChannelInternalErrorOff OBJECT IDENTIFIER ::= { titanEdgeEncoderSchedulerAlarms 19 }

titanEdgeEncoderSchedulerAlarmChannelInternalErrorOn OBJECT IDENTIFIER ::= { titanEdgeEncoderSchedulerAlarms 19 }

titanEdgeDecoderSchedulerAlarmCompositionMCamDuplicatedProgramsOff OBJECT IDENTIFIER ::= { titanEdgeDecoderSchedulerAlarms 44 }

titanEdgeDecoderSchedulerAlarmCompositionMCamDuplicatedProgramsOn OBJECT IDENTIFIER ::= { titanEdgeDecoderSchedulerAlarms 44 }

titanEdgeDecoderSchedulerAlarmCompositionMCamHardwareErrorOff OBJECT IDENTIFIER ::= { titanEdgeDecoderSchedulerAlarms 42 }

titanEdgeDecoderSchedulerAlarmCompositionMCamHardwareErrorOn OBJECT IDENTIFIER ::= { titanEdgeDecoderSchedulerAlarms 42 }

titanEdgeDecoderSchedulerAlarmCompositionMCamLimitsReachedOff OBJECT IDENTIFIER ::= { titanEdgeDecoderSchedulerAlarms 41 }

titanEdgeDecoderSchedulerAlarmCompositionMCamLimitsReachedOn OBJECT IDENTIFIER ::= { titanEdgeDecoderSchedulerAlarms 41 }

titanEdgeDecoderSchedulerAlarm2110Smpte20227ConfigurationInvalidOff OBJECT IDENTIFIER ::= { titanEdgeDecoderSchedulerAlarms 34 }

titanEdgeDecoderSchedulerAlarm2110Smpte20227ConfigurationInvalidOn OBJECT IDENTIFIER ::= { titanEdgeDecoderSchedulerAlarms 34 }

titanEdgeDecoderSchedulerAlarmSystemRivermaxLicenseIssueOff OBJECT IDENTIFIER ::= { titanEdgeDecoderSchedulerAlarms 26 }

titanEdgeDecoderSchedulerAlarmSystemRivermaxLicenseIssueOn OBJECT IDENTIFIER ::= { titanEdgeDecoderSchedulerAlarms 26 }

titanEdgeDecoderSchedulerAlarmSystemExtensionPinConfigurationInvalidOff OBJECT IDENTIFIER ::= { titanEdgeDecoderSchedulerAlarms 24 }

titanEdgeDecoderSchedulerAlarmSystemExtensionPinConfigurationInvalidOn OBJECT IDENTIFIER ::= { titanEdgeDecoderSchedulerAlarms 24 }

titanEdgeDecoderSchedulerAlarmSystemExtensionPinInConflictOff OBJECT IDENTIFIER ::= { titanEdgeDecoderSchedulerAlarms 23 }

titanEdgeDecoderSchedulerAlarmSystemExtensionPinInConflictOn OBJECT IDENTIFIER ::= { titanEdgeDecoderSchedulerAlarms 23 }

titanEdgeDecoderSchedulerAlarmSystemExtensionPinUnknownOff OBJECT IDENTIFIER ::= { titanEdgeDecoderSchedulerAlarms 21 }

titanEdgeDecoderSchedulerAlarmSystemExtensionPinUnknownOn OBJECT IDENTIFIER ::= { titanEdgeDecoderSchedulerAlarms 21 }

titanEdgeDecoderSchedulerAlarmSystemEthernetUnknownOff OBJECT IDENTIFIER ::= { titanEdgeDecoderSchedulerAlarms 30 }

titanEdgeDecoderSchedulerAlarmSystemEthernetUnknownOn OBJECT IDENTIFIER ::= { titanEdgeDecoderSchedulerAlarms 30 }

titanEdgeDecoderSchedulerAlarmSdiOutputGenlockUnlockedOff OBJECT IDENTIFIER ::= { titanEdgeDecoderSchedulerAlarms 22 }

titanEdgeDecoderSchedulerAlarmSdiOutputGenlockUnlockedOn OBJECT IDENTIFIER ::= { titanEdgeDecoderSchedulerAlarms 22 }

titanEdgeDecoderSchedulerAlarmSdiOutputInvalidTimecodeOffsetOff OBJECT IDENTIFIER ::= { titanEdgeDecoderSchedulerAlarms 20 }

titanEdgeDecoderSchedulerAlarmSdiOutputInvalidTimecodeOffsetOn OBJECT IDENTIFIER ::= { titanEdgeDecoderSchedulerAlarms 20 }

titanEdgeDecoderSchedulerAlarmCompositionWatermarkingNotAvailableOff OBJECT IDENTIFIER ::= { titanEdgeDecoderSchedulerAlarms 32 }

titanEdgeDecoderSchedulerAlarmCompositionWatermarkingNotAvailableOn OBJECT IDENTIFIER ::= { titanEdgeDecoderSchedulerAlarms 32 }

titanEdgeDecoderSchedulerAlarmCompositionVideoConstraintIncompatibleOff OBJECT IDENTIFIER ::= { titanEdgeDecoderSchedulerAlarms 18 }

titanEdgeDecoderSchedulerAlarmCompositionVideoConstraintIncompatibleOn OBJECT IDENTIFIER ::= { titanEdgeDecoderSchedulerAlarms 18 }

titanEdgeDecoderSchedulerAlarmCompositionDataSourceMissingOff OBJECT IDENTIFIER ::= { titanEdgeDecoderSchedulerAlarms 10 }

titanEdgeDecoderSchedulerAlarmCompositionDataSourceMissingOn OBJECT IDENTIFIER ::= { titanEdgeDecoderSchedulerAlarms 10 }

titanEdgeDecoderSchedulerAlarmCompositionAudioSourceMissingOff OBJECT IDENTIFIER ::= { titanEdgeDecoderSchedulerAlarms 9 }

titanEdgeDecoderSchedulerAlarmCompositionAudioSourceMissingOn OBJECT IDENTIFIER ::= { titanEdgeDecoderSchedulerAlarms 9 }

titanEdgeDecoderSchedulerAlarmCompositionVideoSourceMissingOff OBJECT IDENTIFIER ::= { titanEdgeDecoderSchedulerAlarms 8 }

titanEdgeDecoderSchedulerAlarmCompositionVideoSourceMissingOn OBJECT IDENTIFIER ::= { titanEdgeDecoderSchedulerAlarms 8 }

titanEdgeDecoderSchedulerAlarmCompositionProgramDecodingPreventedOff OBJECT IDENTIFIER ::= { titanEdgeDecoderSchedulerAlarms 12 }

titanEdgeDecoderSchedulerAlarmCompositionProgramDecodingPreventedOn OBJECT IDENTIFIER ::= { titanEdgeDecoderSchedulerAlarms 12 }

titanEdgeDecoderSchedulerAlarmCompositionProgramScrambledOff OBJECT IDENTIFIER ::= { titanEdgeDecoderSchedulerAlarms 7 }

titanEdgeDecoderSchedulerAlarmCompositionProgramScrambledOn OBJECT IDENTIFIER ::= { titanEdgeDecoderSchedulerAlarms 7 }

titanEdgeDecoderSchedulerAlarmCompositionProgramMissingOff OBJECT IDENTIFIER ::= { titanEdgeDecoderSchedulerAlarms 6 }

titanEdgeDecoderSchedulerAlarmCompositionProgramMissingOn OBJECT IDENTIFIER ::= { titanEdgeDecoderSchedulerAlarms 6 }

titanEdgeDecoderSchedulerAlarmChannelLostOff OBJECT IDENTIFIER ::= { titanEdgeDecoderSchedulerAlarms 33 }

titanEdgeDecoderSchedulerAlarmChannelLostOn OBJECT IDENTIFIER ::= { titanEdgeDecoderSchedulerAlarms 33 }

titanEdgeDecoderSchedulerAlarmLicenseMissingOff OBJECT IDENTIFIER ::= { titanEdgeDecoderSchedulerAlarms 11 }

titanEdgeDecoderSchedulerAlarmLicenseMissingOn OBJECT IDENTIFIER ::= { titanEdgeDecoderSchedulerAlarms 11 }

titanEdgeDecoderSchedulerAlarmTsSmpte20227SkewTooLargeOff OBJECT IDENTIFIER ::= { titanEdgeDecoderSchedulerAlarms 29 }

titanEdgeDecoderSchedulerAlarmTsSmpte20227SkewTooLargeOn OBJECT IDENTIFIER ::= { titanEdgeDecoderSchedulerAlarms 29 }

titanEdgeDecoderSchedulerAlarmTsSmpte20227SignalMissingOff OBJECT IDENTIFIER ::= { titanEdgeDecoderSchedulerAlarms 28 }

titanEdgeDecoderSchedulerAlarmTsSmpte20227SignalMissingOn OBJECT IDENTIFIER ::= { titanEdgeDecoderSchedulerAlarms 28 }

titanEdgeDecoderSchedulerAlarmInternalInputNotConnectedOff OBJECT IDENTIFIER ::= { titanEdgeDecoderSchedulerAlarms 25 }

titanEdgeDecoderSchedulerAlarmInternalInputNotConnectedOn OBJECT IDENTIFIER ::= { titanEdgeDecoderSchedulerAlarms 25 }

titanEdgeDecoderSchedulerAlarmZixiExcessiveJitterOff OBJECT IDENTIFIER ::= { titanEdgeDecoderSchedulerAlarms 5 }

titanEdgeDecoderSchedulerAlarmZixiExcessiveJitterOn OBJECT IDENTIFIER ::= { titanEdgeDecoderSchedulerAlarms 5 }

titanEdgeDecoderSchedulerAlarmZixiInputNotConnectedOff OBJECT IDENTIFIER ::= { titanEdgeDecoderSchedulerAlarms 4 }

titanEdgeDecoderSchedulerAlarmZixiInputNotConnectedOn OBJECT IDENTIFIER ::= { titanEdgeDecoderSchedulerAlarms 4 }

titanEdgeDecoderSchedulerAlarmSatelliteInputSignalNotLockedOff OBJECT IDENTIFIER ::= { titanEdgeDecoderSchedulerAlarms 3 }

titanEdgeDecoderSchedulerAlarmSatelliteInputSignalNotLockedOn OBJECT IDENTIFIER ::= { titanEdgeDecoderSchedulerAlarms 3 }

titanEdgeDecoderSchedulerAlarmTsInputSignalMissingOff OBJECT IDENTIFIER ::= { titanEdgeDecoderSchedulerAlarms 2 }

titanEdgeDecoderSchedulerAlarmTsInputSignalMissingOn OBJECT IDENTIFIER ::= { titanEdgeDecoderSchedulerAlarms 2 }

titanEdgeDecoderSchedulerAlarmChannelInternalErrorOff OBJECT IDENTIFIER ::= { titanEdgeDecoderSchedulerAlarms 19 }

titanEdgeDecoderSchedulerAlarmChannelInternalErrorOn OBJECT IDENTIFIER ::= { titanEdgeDecoderSchedulerAlarms 19 }

titanEdgeApplianceMonitorAlarmSystemPsuFailureOff OBJECT IDENTIFIER ::= { titanEdgeApplianceMonitorAlarms 36 }

titanEdgeApplianceMonitorAlarmSystemPsuFailureOn OBJECT IDENTIFIER ::= { titanEdgeApplianceMonitorAlarms 36 }

titanEdgeApplianceMonitorAlarmSystemEthernetLinkDownOff OBJECT IDENTIFIER ::= { titanEdgeApplianceMonitorAlarms 1 }

titanEdgeApplianceMonitorAlarmSystemEthernetLinkDownOn OBJECT IDENTIFIER ::= { titanEdgeApplianceMonitorAlarms 1 }

titanEdgeGatewaySchedulerAlarmCompositionMCamDuplicatedProgramsOffMonitors OBJECT IDENTIFIER ::= { titanEdgeGatewaySchedulerAlarmCompositionMCamDuplicatedProgramsOn 2 }

titanEdgeGatewaySchedulerAlarmCompositionMCamHardwareErrorOffMonitors OBJECT IDENTIFIER ::= { titanEdgeGatewaySchedulerAlarmCompositionMCamHardwareErrorOn 2 }

titanEdgeGatewaySchedulerAlarmCompositionMCamLimitsReachedOffMonitors OBJECT IDENTIFIER ::= { titanEdgeGatewaySchedulerAlarmCompositionMCamLimitsReachedOn 2 }

titanEdgeGatewaySchedulerAlarmTsNoOutputConnectionOffMonitors OBJECT IDENTIFIER ::= { titanEdgeGatewaySchedulerAlarmTsNoOutputConnectionOn 2 }

titanEdgeGatewaySchedulerAlarmOutputBitrateInvalidOffMonitors OBJECT IDENTIFIER ::= { titanEdgeGatewaySchedulerAlarmOutputBitrateInvalidOn 2 }

titanEdgeGatewaySchedulerAlarmOutputDiscardedPacketsOffMonitors OBJECT IDENTIFIER ::= { titanEdgeGatewaySchedulerAlarmOutputDiscardedPacketsOn 2 }

titanEdgeGatewaySchedulerAlarmCompositionRemuxLimitsReachedOffMonitors OBJECT IDENTIFIER ::= { titanEdgeGatewaySchedulerAlarmCompositionRemuxLimitsReachedOn 2 }

titanEdgeGatewaySchedulerAlarmCompositionRemuxRemappingDetectedOffMonitors OBJECT IDENTIFIER ::= { titanEdgeGatewaySchedulerAlarmCompositionRemuxRemappingDetectedOn 2 }

titanEdgeGatewaySchedulerAlarmCompositionRemuxInputsMissingActivityOffMonitors OBJECT IDENTIFIER ::= { titanEdgeGatewaySchedulerAlarmCompositionRemuxInputsMissingActivityOn 2 }

titanEdgeGatewaySchedulerAlarmCompositionProgramDescramblingPreventedOffMonitors OBJECT IDENTIFIER ::= { titanEdgeGatewaySchedulerAlarmCompositionProgramDescramblingPreventedOn 2 }

titanEdgeGatewaySchedulerAlarmSystemExtensionPinConfigurationInvalidOffMonitors OBJECT IDENTIFIER ::= { titanEdgeGatewaySchedulerAlarmSystemExtensionPinConfigurationInvalidOn 2 }

titanEdgeGatewaySchedulerAlarmSystemExtensionPinInConflictOffMonitors OBJECT IDENTIFIER ::= { titanEdgeGatewaySchedulerAlarmSystemExtensionPinInConflictOn 2 }

titanEdgeGatewaySchedulerAlarmSystemExtensionPinUnknownOffMonitors OBJECT IDENTIFIER ::= { titanEdgeGatewaySchedulerAlarmSystemExtensionPinUnknownOn 2 }

titanEdgeGatewaySchedulerAlarmSystemEthernetUnknownOffMonitors OBJECT IDENTIFIER ::= { titanEdgeGatewaySchedulerAlarmSystemEthernetUnknownOn 2 }

titanEdgeGatewaySchedulerAlarmChannelLostOffMonitors OBJECT IDENTIFIER ::= { titanEdgeGatewaySchedulerAlarmChannelLostOn 2 }

titanEdgeGatewaySchedulerAlarmLicenseMissingOffMonitors OBJECT IDENTIFIER ::= { titanEdgeGatewaySchedulerAlarmLicenseMissingOn 2 }

titanEdgeGatewaySchedulerAlarmTsSmpte20227SkewTooLargeOffMonitors OBJECT IDENTIFIER ::= { titanEdgeGatewaySchedulerAlarmTsSmpte20227SkewTooLargeOn 2 }

titanEdgeGatewaySchedulerAlarmTsSmpte20227SignalMissingOffMonitors OBJECT IDENTIFIER ::= { titanEdgeGatewaySchedulerAlarmTsSmpte20227SignalMissingOn 2 }

titanEdgeGatewaySchedulerAlarmInternalInputNotConnectedOffMonitors OBJECT IDENTIFIER ::= { titanEdgeGatewaySchedulerAlarmInternalInputNotConnectedOn 2 }

titanEdgeGatewaySchedulerAlarmZixiExcessiveJitterOffMonitors OBJECT IDENTIFIER ::= { titanEdgeGatewaySchedulerAlarmZixiExcessiveJitterOn 2 }

titanEdgeGatewaySchedulerAlarmZixiInputNotConnectedOffMonitors OBJECT IDENTIFIER ::= { titanEdgeGatewaySchedulerAlarmZixiInputNotConnectedOn 2 }

titanEdgeGatewaySchedulerAlarmSatelliteInputSignalNotLockedOffMonitors OBJECT IDENTIFIER ::= { titanEdgeGatewaySchedulerAlarmSatelliteInputSignalNotLockedOn 2 }

titanEdgeGatewaySchedulerAlarmTsInputSignalMissingOffMonitors OBJECT IDENTIFIER ::= { titanEdgeGatewaySchedulerAlarmTsInputSignalMissingOn 2 }

titanEdgeGatewaySchedulerAlarmChannelInternalErrorOffMonitors OBJECT IDENTIFIER ::= { titanEdgeGatewaySchedulerAlarmChannelInternalErrorOn 2 }

titanEdgeEncoderSchedulerAlarmTsNoOutputConnectionOffMonitors OBJECT IDENTIFIER ::= { titanEdgeEncoderSchedulerAlarmTsNoOutputConnectionOn 2 }

titanEdgeEncoderSchedulerAlarmSystemRivermaxLicenseIssueOffMonitors OBJECT IDENTIFIER ::= { titanEdgeEncoderSchedulerAlarmSystemRivermaxLicenseIssueOn 2 }

titanEdgeEncoderSchedulerAlarmSystemExtensionPinConfigurationInvalidOffMonitors OBJECT IDENTIFIER ::= { titanEdgeEncoderSchedulerAlarmSystemExtensionPinConfigurationInvalidOn 2 }

titanEdgeEncoderSchedulerAlarmSystemExtensionPinInConflictOffMonitors OBJECT IDENTIFIER ::= { titanEdgeEncoderSchedulerAlarmSystemExtensionPinInConflictOn 2 }

titanEdgeEncoderSchedulerAlarmSystemExtensionPinUnknownOffMonitors OBJECT IDENTIFIER ::= { titanEdgeEncoderSchedulerAlarmSystemExtensionPinUnknownOn 2 }

titanEdgeEncoderSchedulerAlarmSystemEthernetUnknownOffMonitors OBJECT IDENTIFIER ::= { titanEdgeEncoderSchedulerAlarmSystemEthernetUnknownOn 2 }

titanEdgeEncoderSchedulerAlarmOutputBitrateInvalidOffMonitors OBJECT IDENTIFIER ::= { titanEdgeEncoderSchedulerAlarmOutputBitrateInvalidOn 2 }

titanEdgeEncoderSchedulerAlarmOutputDiscardedPacketsOffMonitors OBJECT IDENTIFIER ::= { titanEdgeEncoderSchedulerAlarmOutputDiscardedPacketsOn 2 }

titanEdgeEncoderSchedulerAlarmCompositionAudioSourceInactiveOffMonitors OBJECT IDENTIFIER ::= { titanEdgeEncoderSchedulerAlarmCompositionAudioSourceInactiveOn 2 }

titanEdgeEncoderSchedulerAlarmCompositionAudioSourceIncompatibleOffMonitors OBJECT IDENTIFIER ::= { titanEdgeEncoderSchedulerAlarmCompositionAudioSourceIncompatibleOn 2 }

titanEdgeEncoderSchedulerAlarmCompositionAudioSourceMissingOffMonitors OBJECT IDENTIFIER ::= { titanEdgeEncoderSchedulerAlarmCompositionAudioSourceMissingOn 2 }

titanEdgeEncoderSchedulerAlarmCompositionVideoSourceIncompatibleOffMonitors OBJECT IDENTIFIER ::= { titanEdgeEncoderSchedulerAlarmCompositionVideoSourceIncompatibleOn 2 }

titanEdgeEncoderSchedulerAlarmCompositionVideoSourceNotSupportedOffMonitors OBJECT IDENTIFIER ::= { titanEdgeEncoderSchedulerAlarmCompositionVideoSourceNotSupportedOn 2 }

titanEdgeEncoderSchedulerAlarmCompositionVideoSourceMissingOffMonitors OBJECT IDENTIFIER ::= { titanEdgeEncoderSchedulerAlarmCompositionVideoSourceMissingOn 2 }

titanEdgeEncoderSchedulerAlarmTsOccupancyBitrateInvalidOffMonitors OBJECT IDENTIFIER ::= { titanEdgeEncoderSchedulerAlarmTsOccupancyBitrateInvalidOn 2 }

titanEdgeEncoderSchedulerAlarmTsOutputBitrateDifferentOffMonitors OBJECT IDENTIFIER ::= { titanEdgeEncoderSchedulerAlarmTsOutputBitrateDifferentOn 2 }

titanEdgeEncoderSchedulerAlarmChannelLostOffMonitors OBJECT IDENTIFIER ::= { titanEdgeEncoderSchedulerAlarmChannelLostOn 2 }

titanEdgeEncoderSchedulerAlarmLicenseMissingOffMonitors OBJECT IDENTIFIER ::= { titanEdgeEncoderSchedulerAlarmLicenseMissingOn 2 }

titanEdgeEncoderSchedulerAlarmChannelInternalErrorOffMonitors OBJECT IDENTIFIER ::= { titanEdgeEncoderSchedulerAlarmChannelInternalErrorOn 2 }

titanEdgeDecoderSchedulerAlarmCompositionMCamDuplicatedProgramsOffMonitors OBJECT IDENTIFIER ::= { titanEdgeDecoderSchedulerAlarmCompositionMCamDuplicatedProgramsOn 2 }

titanEdgeDecoderSchedulerAlarmCompositionMCamHardwareErrorOffMonitors OBJECT IDENTIFIER ::= { titanEdgeDecoderSchedulerAlarmCompositionMCamHardwareErrorOn 2 }

titanEdgeDecoderSchedulerAlarmCompositionMCamLimitsReachedOffMonitors OBJECT IDENTIFIER ::= { titanEdgeDecoderSchedulerAlarmCompositionMCamLimitsReachedOn 2 }

titanEdgeDecoderSchedulerAlarm2110Smpte20227ConfigurationInvalidOffMonitors OBJECT IDENTIFIER ::= { titanEdgeDecoderSchedulerAlarm2110Smpte20227ConfigurationInvalidOn 2 }

titanEdgeDecoderSchedulerAlarmSystemRivermaxLicenseIssueOffMonitors OBJECT IDENTIFIER ::= { titanEdgeDecoderSchedulerAlarmSystemRivermaxLicenseIssueOn 2 }

titanEdgeDecoderSchedulerAlarmSystemExtensionPinConfigurationInvalidOffMonitors OBJECT IDENTIFIER ::= { titanEdgeDecoderSchedulerAlarmSystemExtensionPinConfigurationInvalidOn 2 }

titanEdgeDecoderSchedulerAlarmSystemExtensionPinInConflictOffMonitors OBJECT IDENTIFIER ::= { titanEdgeDecoderSchedulerAlarmSystemExtensionPinInConflictOn 2 }

titanEdgeDecoderSchedulerAlarmSystemExtensionPinUnknownOffMonitors OBJECT IDENTIFIER ::= { titanEdgeDecoderSchedulerAlarmSystemExtensionPinUnknownOn 2 }

titanEdgeDecoderSchedulerAlarmSystemEthernetUnknownOffMonitors OBJECT IDENTIFIER ::= { titanEdgeDecoderSchedulerAlarmSystemEthernetUnknownOn 2 }

titanEdgeDecoderSchedulerAlarmSdiOutputGenlockUnlockedOffMonitors OBJECT IDENTIFIER ::= { titanEdgeDecoderSchedulerAlarmSdiOutputGenlockUnlockedOn 2 }

titanEdgeDecoderSchedulerAlarmSdiOutputInvalidTimecodeOffsetOffMonitors OBJECT IDENTIFIER ::= { titanEdgeDecoderSchedulerAlarmSdiOutputInvalidTimecodeOffsetOn 2 }

titanEdgeDecoderSchedulerAlarmCompositionWatermarkingNotAvailableOffMonitors OBJECT IDENTIFIER ::= { titanEdgeDecoderSchedulerAlarmCompositionWatermarkingNotAvailableOn 2 }

titanEdgeDecoderSchedulerAlarmCompositionVideoConstraintIncompatibleOffMonitors OBJECT IDENTIFIER ::= { titanEdgeDecoderSchedulerAlarmCompositionVideoConstraintIncompatibleOn 2 }

titanEdgeDecoderSchedulerAlarmCompositionDataSourceMissingOffMonitors OBJECT IDENTIFIER ::= { titanEdgeDecoderSchedulerAlarmCompositionDataSourceMissingOn 2 }

titanEdgeDecoderSchedulerAlarmCompositionAudioSourceMissingOffMonitors OBJECT IDENTIFIER ::= { titanEdgeDecoderSchedulerAlarmCompositionAudioSourceMissingOn 2 }

titanEdgeDecoderSchedulerAlarmCompositionVideoSourceMissingOffMonitors OBJECT IDENTIFIER ::= { titanEdgeDecoderSchedulerAlarmCompositionVideoSourceMissingOn 2 }

titanEdgeDecoderSchedulerAlarmCompositionProgramDecodingPreventedOffMonitors OBJECT IDENTIFIER ::= { titanEdgeDecoderSchedulerAlarmCompositionProgramDecodingPreventedOn 2 }

titanEdgeDecoderSchedulerAlarmCompositionProgramScrambledOffMonitors OBJECT IDENTIFIER ::= { titanEdgeDecoderSchedulerAlarmCompositionProgramScrambledOn 2 }

titanEdgeDecoderSchedulerAlarmCompositionProgramMissingOffMonitors OBJECT IDENTIFIER ::= { titanEdgeDecoderSchedulerAlarmCompositionProgramMissingOn 2 }

titanEdgeDecoderSchedulerAlarmChannelLostOffMonitors OBJECT IDENTIFIER ::= { titanEdgeDecoderSchedulerAlarmChannelLostOn 2 }

titanEdgeDecoderSchedulerAlarmLicenseMissingOffMonitors OBJECT IDENTIFIER ::= { titanEdgeDecoderSchedulerAlarmLicenseMissingOn 2 }

titanEdgeDecoderSchedulerAlarmTsSmpte20227SkewTooLargeOffMonitors OBJECT IDENTIFIER ::= { titanEdgeDecoderSchedulerAlarmTsSmpte20227SkewTooLargeOn 2 }

titanEdgeDecoderSchedulerAlarmTsSmpte20227SignalMissingOffMonitors OBJECT IDENTIFIER ::= { titanEdgeDecoderSchedulerAlarmTsSmpte20227SignalMissingOn 2 }

titanEdgeDecoderSchedulerAlarmInternalInputNotConnectedOffMonitors OBJECT IDENTIFIER ::= { titanEdgeDecoderSchedulerAlarmInternalInputNotConnectedOn 2 }

titanEdgeDecoderSchedulerAlarmZixiExcessiveJitterOffMonitors OBJECT IDENTIFIER ::= { titanEdgeDecoderSchedulerAlarmZixiExcessiveJitterOn 2 }

titanEdgeDecoderSchedulerAlarmZixiInputNotConnectedOffMonitors OBJECT IDENTIFIER ::= { titanEdgeDecoderSchedulerAlarmZixiInputNotConnectedOn 2 }

titanEdgeDecoderSchedulerAlarmSatelliteInputSignalNotLockedOffMonitors OBJECT IDENTIFIER ::= { titanEdgeDecoderSchedulerAlarmSatelliteInputSignalNotLockedOn 2 }

titanEdgeDecoderSchedulerAlarmTsInputSignalMissingOffMonitors OBJECT IDENTIFIER ::= { titanEdgeDecoderSchedulerAlarmTsInputSignalMissingOn 2 }

titanEdgeDecoderSchedulerAlarmChannelInternalErrorOffMonitors OBJECT IDENTIFIER ::= { titanEdgeDecoderSchedulerAlarmChannelInternalErrorOn 2 }

titanEdgeApplianceMonitorAlarmSystemPsuFailureOffMonitors OBJECT IDENTIFIER ::= { titanEdgeApplianceMonitorAlarmSystemPsuFailureOn 2 }

titanEdgeApplianceMonitorAlarmSystemEthernetLinkDownOffMonitors OBJECT IDENTIFIER ::= { titanEdgeApplianceMonitorAlarmSystemEthernetLinkDownOn 2 }

titanEdgeNotificationGroup NOTIFICATION-GROUP
    NOTIFICATIONS {
        titanEdgeApplianceMonitorLogSystemStartedNotification,
        titanEdgeApplianceMonitorLogSystemStoppedNotification,
        titanEdgeApplianceMonitorLogSystemEthernetIgmpVersionChangedNotification,
        titanEdgeApplianceMonitorLogDvbSsuChannelUpdateNotification,
        titanEdgeApplianceMonitorLogDvbSsuLicenseUpdateNotification,
        titanEdgeApplianceMonitorLogDvbSsuFirmwareUpdatingNotification,
        titanEdgeApplianceMonitorLogDvbSsuAssetUpdateNotification,
        titanEdgeApplianceMonitorLogDvbSsuAssetDeletedNotification,
        titanEdgeApplianceMonitorLogDvbSsuFirmwareUpdateRejectedNotification,
        titanEdgeApplianceMonitorAlarmSystemEthernetLinkDownOnNotification,
        titanEdgeApplianceMonitorAlarmSystemEthernetLinkDownOffNotification,
        titanEdgeApplianceMonitorAlarmSystemPsuFailureOnNotification,
        titanEdgeApplianceMonitorAlarmSystemPsuFailureOffNotification,
        titanEdgeDecoderApiLogChannelAddedNotification,
        titanEdgeDecoderApiLogChannelDeletedNotification,
        titanEdgeDecoderApiLogChannelModifiedNotification,
        titanEdgeDecoderSchedulerLogChannelStartedNotification,
        titanEdgeDecoderSchedulerLogChannelStoppedNotification,
        titanEdgeDecoderSchedulerLogChannelFailoverInputChangedNotification,
        titanEdgeDecoderSchedulerLogOutputSplicingInProgressNotification,
        titanEdgeDecoderSchedulerLogOutputSplicingDoneNotification,
        titanEdgeDecoderSchedulerAlarmTsInputSignalMissingOnNotification,
        titanEdgeDecoderSchedulerAlarmTsInputSignalMissingOffNotification,
        titanEdgeDecoderSchedulerAlarmSatelliteInputSignalNotLockedOnNotification,
        titanEdgeDecoderSchedulerAlarmSatelliteInputSignalNotLockedOffNotification,
        titanEdgeDecoderSchedulerAlarmZixiInputNotConnectedOnNotification,
        titanEdgeDecoderSchedulerAlarmZixiInputNotConnectedOffNotification,
        titanEdgeDecoderSchedulerAlarmZixiExcessiveJitterOnNotification,
        titanEdgeDecoderSchedulerAlarmZixiExcessiveJitterOffNotification,
        titanEdgeDecoderSchedulerAlarmCompositionProgramMissingOnNotification,
        titanEdgeDecoderSchedulerAlarmCompositionProgramMissingOffNotification,
        titanEdgeDecoderSchedulerAlarmCompositionProgramScrambledOnNotification,
        titanEdgeDecoderSchedulerAlarmCompositionProgramScrambledOffNotification,
        titanEdgeDecoderSchedulerAlarmCompositionVideoSourceMissingOnNotification,
        titanEdgeDecoderSchedulerAlarmCompositionVideoSourceMissingOffNotification,
        titanEdgeDecoderSchedulerAlarmCompositionAudioSourceMissingOnNotification,
        titanEdgeDecoderSchedulerAlarmCompositionAudioSourceMissingOffNotification,
        titanEdgeDecoderSchedulerAlarmCompositionDataSourceMissingOnNotification,
        titanEdgeDecoderSchedulerAlarmCompositionDataSourceMissingOffNotification,
        titanEdgeDecoderSchedulerAlarmLicenseMissingOnNotification,
        titanEdgeDecoderSchedulerAlarmLicenseMissingOffNotification,
        titanEdgeDecoderSchedulerAlarmCompositionProgramDecodingPreventedOnNotification,
        titanEdgeDecoderSchedulerAlarmCompositionProgramDecodingPreventedOffNotification,
        titanEdgeDecoderSchedulerAlarmCompositionVideoConstraintIncompatibleOnNotification,
        titanEdgeDecoderSchedulerAlarmCompositionVideoConstraintIncompatibleOffNotification,
        titanEdgeDecoderSchedulerAlarmChannelInternalErrorOnNotification,
        titanEdgeDecoderSchedulerAlarmChannelInternalErrorOffNotification,
        titanEdgeDecoderSchedulerAlarmSdiOutputInvalidTimecodeOffsetOnNotification,
        titanEdgeDecoderSchedulerAlarmSdiOutputInvalidTimecodeOffsetOffNotification,
        titanEdgeDecoderSchedulerAlarmSystemExtensionPinUnknownOnNotification,
        titanEdgeDecoderSchedulerAlarmSystemExtensionPinUnknownOffNotification,
        titanEdgeDecoderSchedulerAlarmSdiOutputGenlockUnlockedOnNotification,
        titanEdgeDecoderSchedulerAlarmSdiOutputGenlockUnlockedOffNotification,
        titanEdgeDecoderSchedulerAlarmSystemExtensionPinInConflictOnNotification,
        titanEdgeDecoderSchedulerAlarmSystemExtensionPinInConflictOffNotification,
        titanEdgeDecoderSchedulerAlarmSystemExtensionPinConfigurationInvalidOnNotification,
        titanEdgeDecoderSchedulerAlarmSystemExtensionPinConfigurationInvalidOffNotification,
        titanEdgeDecoderSchedulerAlarmInternalInputNotConnectedOnNotification,
        titanEdgeDecoderSchedulerAlarmInternalInputNotConnectedOffNotification,
        titanEdgeDecoderSchedulerAlarmSystemRivermaxLicenseIssueOnNotification,
        titanEdgeDecoderSchedulerAlarmSystemRivermaxLicenseIssueOffNotification,
        titanEdgeDecoderSchedulerAlarmTsSmpte20227SignalMissingOnNotification,
        titanEdgeDecoderSchedulerAlarmTsSmpte20227SignalMissingOffNotification,
        titanEdgeDecoderSchedulerAlarmTsSmpte20227SkewTooLargeOnNotification,
        titanEdgeDecoderSchedulerAlarmTsSmpte20227SkewTooLargeOffNotification,
        titanEdgeDecoderSchedulerAlarmSystemEthernetUnknownOnNotification,
        titanEdgeDecoderSchedulerAlarmSystemEthernetUnknownOffNotification,
        titanEdgeDecoderSchedulerAlarmCompositionWatermarkingNotAvailableOnNotification,
        titanEdgeDecoderSchedulerAlarmCompositionWatermarkingNotAvailableOffNotification,
        titanEdgeDecoderSchedulerAlarmChannelLostOnNotification,
        titanEdgeDecoderSchedulerAlarmChannelLostOffNotification,
        titanEdgeDecoderSchedulerAlarm2110Smpte20227ConfigurationInvalidOnNotification,
        titanEdgeDecoderSchedulerAlarm2110Smpte20227ConfigurationInvalidOffNotification,
        titanEdgeDecoderSchedulerAlarmCompositionMCamLimitsReachedOnNotification,
        titanEdgeDecoderSchedulerAlarmCompositionMCamLimitsReachedOffNotification,
        titanEdgeDecoderSchedulerAlarmCompositionMCamHardwareErrorOnNotification,
        titanEdgeDecoderSchedulerAlarmCompositionMCamHardwareErrorOffNotification,
        titanEdgeDecoderSchedulerAlarmCompositionMCamDuplicatedProgramsOnNotification,
        titanEdgeDecoderSchedulerAlarmCompositionMCamDuplicatedProgramsOffNotification,
        titanEdgeDecoderProcessingLogProcessingFailureNotification,
        titanEdgeEncoderApiLogChannelAddedNotification,
        titanEdgeEncoderApiLogChannelDeletedNotification,
        titanEdgeEncoderApiLogChannelModifiedNotification,
        titanEdgeEncoderSchedulerLogChannelStartedNotification,
        titanEdgeEncoderSchedulerLogChannelStoppedNotification,
        titanEdgeEncoderSchedulerLogChannelFailoverInputChangedNotification,
        titanEdgeEncoderSchedulerAlarmCompositionVideoSourceMissingOnNotification,
        titanEdgeEncoderSchedulerAlarmCompositionVideoSourceMissingOffNotification,
        titanEdgeEncoderSchedulerAlarmCompositionAudioSourceMissingOnNotification,
        titanEdgeEncoderSchedulerAlarmCompositionAudioSourceMissingOffNotification,
        titanEdgeEncoderSchedulerAlarmLicenseMissingOnNotification,
        titanEdgeEncoderSchedulerAlarmLicenseMissingOffNotification,
        titanEdgeEncoderSchedulerAlarmCompositionVideoSourceIncompatibleOnNotification,
        titanEdgeEncoderSchedulerAlarmCompositionVideoSourceIncompatibleOffNotification,
        titanEdgeEncoderSchedulerAlarmCompositionVideoSourceNotSupportedOnNotification,
        titanEdgeEncoderSchedulerAlarmCompositionVideoSourceNotSupportedOffNotification,
        titanEdgeEncoderSchedulerAlarmCompositionAudioSourceIncompatibleOnNotification,
        titanEdgeEncoderSchedulerAlarmCompositionAudioSourceIncompatibleOffNotification,
        titanEdgeEncoderSchedulerAlarmCompositionAudioSourceInactiveOnNotification,
        titanEdgeEncoderSchedulerAlarmCompositionAudioSourceInactiveOffNotification,
        titanEdgeEncoderSchedulerAlarmTsOutputBitrateDifferentOnNotification,
        titanEdgeEncoderSchedulerAlarmTsOutputBitrateDifferentOffNotification,
        titanEdgeEncoderSchedulerAlarmChannelInternalErrorOnNotification,
        titanEdgeEncoderSchedulerAlarmChannelInternalErrorOffNotification,
        titanEdgeEncoderSchedulerAlarmSystemExtensionPinUnknownOnNotification,
        titanEdgeEncoderSchedulerAlarmSystemExtensionPinUnknownOffNotification,
        titanEdgeEncoderSchedulerAlarmSystemExtensionPinInConflictOnNotification,
        titanEdgeEncoderSchedulerAlarmSystemExtensionPinInConflictOffNotification,
        titanEdgeEncoderSchedulerAlarmSystemExtensionPinConfigurationInvalidOnNotification,
        titanEdgeEncoderSchedulerAlarmSystemExtensionPinConfigurationInvalidOffNotification,
        titanEdgeEncoderSchedulerAlarmSystemRivermaxLicenseIssueOnNotification,
        titanEdgeEncoderSchedulerAlarmSystemRivermaxLicenseIssueOffNotification,
        titanEdgeEncoderSchedulerAlarmTsOccupancyBitrateInvalidOnNotification,
        titanEdgeEncoderSchedulerAlarmTsOccupancyBitrateInvalidOffNotification,
        titanEdgeEncoderSchedulerAlarmSystemEthernetUnknownOnNotification,
        titanEdgeEncoderSchedulerAlarmSystemEthernetUnknownOffNotification,
        titanEdgeEncoderSchedulerAlarmChannelLostOnNotification,
        titanEdgeEncoderSchedulerAlarmChannelLostOffNotification,
        titanEdgeEncoderSchedulerAlarmOutputDiscardedPacketsOnNotification,
        titanEdgeEncoderSchedulerAlarmOutputDiscardedPacketsOffNotification,
        titanEdgeEncoderSchedulerAlarmTsNoOutputConnectionOnNotification,
        titanEdgeEncoderSchedulerAlarmTsNoOutputConnectionOffNotification,
        titanEdgeEncoderSchedulerAlarmOutputBitrateInvalidOnNotification,
        titanEdgeEncoderSchedulerAlarmOutputBitrateInvalidOffNotification,
        titanEdgeEncoderProcessingLogProcessingFailureNotification,
        titanEdgeGatewayApiLogChannelAddedNotification,
        titanEdgeGatewayApiLogChannelDeletedNotification,
        titanEdgeGatewayApiLogChannelModifiedNotification,
        titanEdgeGatewaySchedulerLogChannelStartedNotification,
        titanEdgeGatewaySchedulerLogChannelStoppedNotification,
        titanEdgeGatewaySchedulerLogChannelFailoverInputChangedNotification,
        titanEdgeGatewaySchedulerAlarmTsInputSignalMissingOnNotification,
        titanEdgeGatewaySchedulerAlarmTsInputSignalMissingOffNotification,
        titanEdgeGatewaySchedulerAlarmSatelliteInputSignalNotLockedOnNotification,
        titanEdgeGatewaySchedulerAlarmSatelliteInputSignalNotLockedOffNotification,
        titanEdgeGatewaySchedulerAlarmZixiInputNotConnectedOnNotification,
        titanEdgeGatewaySchedulerAlarmZixiInputNotConnectedOffNotification,
        titanEdgeGatewaySchedulerAlarmZixiExcessiveJitterOnNotification,
        titanEdgeGatewaySchedulerAlarmZixiExcessiveJitterOffNotification,
        titanEdgeGatewaySchedulerAlarmLicenseMissingOnNotification,
        titanEdgeGatewaySchedulerAlarmLicenseMissingOffNotification,
        titanEdgeGatewaySchedulerAlarmChannelInternalErrorOnNotification,
        titanEdgeGatewaySchedulerAlarmChannelInternalErrorOffNotification,
        titanEdgeGatewaySchedulerAlarmSystemExtensionPinUnknownOnNotification,
        titanEdgeGatewaySchedulerAlarmSystemExtensionPinUnknownOffNotification,
        titanEdgeGatewaySchedulerAlarmSystemExtensionPinInConflictOnNotification,
        titanEdgeGatewaySchedulerAlarmSystemExtensionPinInConflictOffNotification,
        titanEdgeGatewaySchedulerAlarmSystemExtensionPinConfigurationInvalidOnNotification,
        titanEdgeGatewaySchedulerAlarmSystemExtensionPinConfigurationInvalidOffNotification,
        titanEdgeGatewaySchedulerAlarmInternalInputNotConnectedOnNotification,
        titanEdgeGatewaySchedulerAlarmInternalInputNotConnectedOffNotification,
        titanEdgeGatewaySchedulerAlarmTsSmpte20227SignalMissingOnNotification,
        titanEdgeGatewaySchedulerAlarmTsSmpte20227SignalMissingOffNotification,
        titanEdgeGatewaySchedulerAlarmTsSmpte20227SkewTooLargeOnNotification,
        titanEdgeGatewaySchedulerAlarmTsSmpte20227SkewTooLargeOffNotification,
        titanEdgeGatewaySchedulerAlarmSystemEthernetUnknownOnNotification,
        titanEdgeGatewaySchedulerAlarmSystemEthernetUnknownOffNotification,
        titanEdgeGatewaySchedulerAlarmCompositionProgramDescramblingPreventedOnNotification,
        titanEdgeGatewaySchedulerAlarmCompositionProgramDescramblingPreventedOffNotification,
        titanEdgeGatewaySchedulerAlarmChannelLostOnNotification,
        titanEdgeGatewaySchedulerAlarmChannelLostOffNotification,
        titanEdgeGatewaySchedulerAlarmOutputDiscardedPacketsOnNotification,
        titanEdgeGatewaySchedulerAlarmOutputDiscardedPacketsOffNotification,
        titanEdgeGatewaySchedulerAlarmCompositionRemuxRemappingDetectedOnNotification,
        titanEdgeGatewaySchedulerAlarmCompositionRemuxRemappingDetectedOffNotification,
        titanEdgeGatewaySchedulerAlarmCompositionRemuxInputsMissingActivityOnNotification,
        titanEdgeGatewaySchedulerAlarmCompositionRemuxInputsMissingActivityOffNotification,
        titanEdgeGatewaySchedulerAlarmCompositionRemuxLimitsReachedOnNotification,
        titanEdgeGatewaySchedulerAlarmCompositionRemuxLimitsReachedOffNotification,
        titanEdgeGatewaySchedulerAlarmTsNoOutputConnectionOnNotification,
        titanEdgeGatewaySchedulerAlarmTsNoOutputConnectionOffNotification,
        titanEdgeGatewaySchedulerAlarmCompositionMCamLimitsReachedOnNotification,
        titanEdgeGatewaySchedulerAlarmCompositionMCamLimitsReachedOffNotification,
        titanEdgeGatewaySchedulerAlarmCompositionMCamHardwareErrorOnNotification,
        titanEdgeGatewaySchedulerAlarmCompositionMCamHardwareErrorOffNotification,
        titanEdgeGatewaySchedulerAlarmOutputBitrateInvalidOnNotification,
        titanEdgeGatewaySchedulerAlarmOutputBitrateInvalidOffNotification,
        titanEdgeGatewaySchedulerAlarmCompositionMCamDuplicatedProgramsOnNotification,
        titanEdgeGatewaySchedulerAlarmCompositionMCamDuplicatedProgramsOffNotification,
        titanEdgeGatewayProcessingLogProcessingFailureNotification
    }
    STATUS current
    DESCRIPTION "It contains all notifications."
    ::= { titanEdgeGroups 1 }

titanEdgeCompliance MODULE-COMPLIANCE
    STATUS current
    DESCRIPTION "Compliance."
    MODULE
    MANDATORY-GROUPS {
        titanEdgeNotificationGroup
    }
    ::= { titanEdgeCompliances 1 }

titanEdgeApplianceMonitorLogSystemStartedNotification NOTIFICATION-TYPE
    STATUS current
    DESCRIPTION "System started"
    ::= { titanEdgeApplianceMonitorLogs 1 }

titanEdgeApplianceMonitorLogSystemStoppedNotification NOTIFICATION-TYPE
    STATUS current
    DESCRIPTION "System stopped"
    ::= { titanEdgeApplianceMonitorLogs 2 }

titanEdgeApplianceMonitorLogSystemEthernetIgmpVersionChangedNotification NOTIFICATION-TYPE
    OBJECTS {
        titanEdgeApplianceMonitorLogSystemEthernetIgmpVersionChangedId
    }
    STATUS current
    DESCRIPTION "Ethernet IGMP version changed"
    ::= { titanEdgeApplianceMonitorLogs 3 }

titanEdgeApplianceMonitorLogSystemEthernetIgmpVersionChangedId OBJECT-TYPE
    SYNTAX DisplayString
    MAX-ACCESS read-only
    STATUS current
    DESCRIPTION "."
    ::= { titanEdgeApplianceMonitorLogs 3 2 }

titanEdgeApplianceMonitorLogDvbSsuChannelUpdateNotification NOTIFICATION-TYPE
    OBJECTS {
        titanEdgeApplianceMonitorLogDvbSsuChannelUpdateId,
        titanEdgeApplianceMonitorLogDvbSsuChannelUpdateName
    }
    STATUS current
    DESCRIPTION "DVB-SSU channel update"
    ::= { titanEdgeApplianceMonitorLogs 11 }

titanEdgeApplianceMonitorLogDvbSsuChannelUpdateId OBJECT-TYPE
    SYNTAX DisplayString
    MAX-ACCESS read-only
    STATUS current
    DESCRIPTION "."
    ::= { titanEdgeApplianceMonitorLogs 11 2 }

titanEdgeApplianceMonitorLogDvbSsuChannelUpdateName OBJECT-TYPE
    SYNTAX DisplayString
    MAX-ACCESS read-only
    STATUS current
    DESCRIPTION "."
    ::= { titanEdgeApplianceMonitorLogs 11 2 }

titanEdgeApplianceMonitorLogDvbSsuLicenseUpdateNotification NOTIFICATION-TYPE
    OBJECTS {
        titanEdgeApplianceMonitorLogDvbSsuLicenseUpdateId,
        titanEdgeApplianceMonitorLogDvbSsuLicenseUpdateName
    }
    STATUS current
    DESCRIPTION "DVB-SSU license update"
    ::= { titanEdgeApplianceMonitorLogs 12 }

titanEdgeApplianceMonitorLogDvbSsuLicenseUpdateId OBJECT-TYPE
    SYNTAX DisplayString
    MAX-ACCESS read-only
    STATUS current
    DESCRIPTION "."
    ::= { titanEdgeApplianceMonitorLogs 12 2 }

titanEdgeApplianceMonitorLogDvbSsuLicenseUpdateName OBJECT-TYPE
    SYNTAX DisplayString
    MAX-ACCESS read-only
    STATUS current
    DESCRIPTION "."
    ::= { titanEdgeApplianceMonitorLogs 12 2 }

titanEdgeApplianceMonitorLogDvbSsuFirmwareUpdatingNotification NOTIFICATION-TYPE
    OBJECTS {
        titanEdgeApplianceMonitorLogDvbSsuFirmwareUpdatingId,
        titanEdgeApplianceMonitorLogDvbSsuFirmwareUpdatingName
    }
    STATUS current
    DESCRIPTION "DVB-SSU firmware updating"
    ::= { titanEdgeApplianceMonitorLogs 13 }

titanEdgeApplianceMonitorLogDvbSsuFirmwareUpdatingId OBJECT-TYPE
    SYNTAX DisplayString
    MAX-ACCESS read-only
    STATUS current
    DESCRIPTION "."
    ::= { titanEdgeApplianceMonitorLogs 13 2 }

titanEdgeApplianceMonitorLogDvbSsuFirmwareUpdatingName OBJECT-TYPE
    SYNTAX DisplayString
    MAX-ACCESS read-only
    STATUS current
    DESCRIPTION "."
    ::= { titanEdgeApplianceMonitorLogs 13 2 }

titanEdgeApplianceMonitorLogDvbSsuAssetUpdateNotification NOTIFICATION-TYPE
    OBJECTS {
        titanEdgeApplianceMonitorLogDvbSsuAssetUpdateId,
        titanEdgeApplianceMonitorLogDvbSsuAssetUpdateName
    }
    STATUS current
    DESCRIPTION "DVB-SSU asset update"
    ::= { titanEdgeApplianceMonitorLogs 14 }

titanEdgeApplianceMonitorLogDvbSsuAssetUpdateId OBJECT-TYPE
    SYNTAX DisplayString
    MAX-ACCESS read-only
    STATUS current
    DESCRIPTION "."
    ::= { titanEdgeApplianceMonitorLogs 14 2 }

titanEdgeApplianceMonitorLogDvbSsuAssetUpdateName OBJECT-TYPE
    SYNTAX DisplayString
    MAX-ACCESS read-only
    STATUS current
    DESCRIPTION "."
    ::= { titanEdgeApplianceMonitorLogs 14 2 }

titanEdgeApplianceMonitorLogDvbSsuAssetDeletedNotification NOTIFICATION-TYPE
    OBJECTS {
        titanEdgeApplianceMonitorLogDvbSsuAssetDeletedId,
        titanEdgeApplianceMonitorLogDvbSsuAssetDeletedName
    }
    STATUS current
    DESCRIPTION "DVB-SSU asset deleted"
    ::= { titanEdgeApplianceMonitorLogs 15 }

titanEdgeApplianceMonitorLogDvbSsuAssetDeletedId OBJECT-TYPE
    SYNTAX DisplayString
    MAX-ACCESS read-only
    STATUS current
    DESCRIPTION "."
    ::= { titanEdgeApplianceMonitorLogs 15 2 }

titanEdgeApplianceMonitorLogDvbSsuAssetDeletedName OBJECT-TYPE
    SYNTAX DisplayString
    MAX-ACCESS read-only
    STATUS current
    DESCRIPTION "."
    ::= { titanEdgeApplianceMonitorLogs 15 2 }

titanEdgeApplianceMonitorLogDvbSsuFirmwareUpdateRejectedNotification NOTIFICATION-TYPE
    OBJECTS {
        titanEdgeApplianceMonitorLogDvbSsuFirmwareUpdateRejectedId,
        titanEdgeApplianceMonitorLogDvbSsuFirmwareUpdateRejectedName
    }
    STATUS current
    DESCRIPTION "DVB-SSU firmware update rejected"
    ::= { titanEdgeApplianceMonitorLogs 16 }

titanEdgeApplianceMonitorLogDvbSsuFirmwareUpdateRejectedId OBJECT-TYPE
    SYNTAX DisplayString
    MAX-ACCESS read-only
    STATUS current
    DESCRIPTION "."
    ::= { titanEdgeApplianceMonitorLogs 16 2 }

titanEdgeApplianceMonitorLogDvbSsuFirmwareUpdateRejectedName OBJECT-TYPE
    SYNTAX DisplayString
    MAX-ACCESS read-only
    STATUS current
    DESCRIPTION "."
    ::= { titanEdgeApplianceMonitorLogs 16 2 }

titanEdgeApplianceMonitorAlarmSystemEthernetLinkDownOnNotification NOTIFICATION-TYPE
    OBJECTS {
        titanEdgeApplianceMonitorAlarmSystemEthernetLinkDownOnId
    }
    STATUS current
    DESCRIPTION "Ethernet link down"
    ::= { titanEdgeApplianceMonitorAlarmSystemEthernetLinkDownOn 1 }

titanEdgeApplianceMonitorAlarmSystemEthernetLinkDownOnId OBJECT-TYPE
    SYNTAX DisplayString
    MAX-ACCESS read-only
    STATUS current
    DESCRIPTION "."
    ::= { titanEdgeApplianceMonitorAlarmSystemEthernetLinkDownOn 1 2 }

titanEdgeApplianceMonitorAlarmSystemEthernetLinkDownOffNotification NOTIFICATION-TYPE
    OBJECTS {
        titanEdgeApplianceMonitorAlarmSystemEthernetLinkDownOffId
    }
    STATUS current
    DESCRIPTION "Ethernet link down"
    ::= { titanEdgeApplianceMonitorAlarmSystemEthernetLinkDownOn 2 }

titanEdgeApplianceMonitorAlarmSystemEthernetLinkDownOffId OBJECT-TYPE
    SYNTAX DisplayString
    MAX-ACCESS read-only
    STATUS current
    DESCRIPTION "."
    ::= { titanEdgeApplianceMonitorAlarmSystemEthernetLinkDownOffMonitors 2 }

titanEdgeApplianceMonitorAlarmSystemPsuFailureOnNotification NOTIFICATION-TYPE
    OBJECTS {
        titanEdgeApplianceMonitorAlarmSystemPsuFailureOnId
    }
    STATUS current
    DESCRIPTION "Power supply unit failure"
    ::= { titanEdgeApplianceMonitorAlarmSystemPsuFailureOn 1 }

titanEdgeApplianceMonitorAlarmSystemPsuFailureOnId OBJECT-TYPE
    SYNTAX INTEGER
    MAX-ACCESS read-only
    STATUS current
    DESCRIPTION "."
    ::= { titanEdgeApplianceMonitorAlarmSystemPsuFailureOn 1 2 }

titanEdgeApplianceMonitorAlarmSystemPsuFailureOffNotification NOTIFICATION-TYPE
    OBJECTS {
        titanEdgeApplianceMonitorAlarmSystemPsuFailureOffId
    }
    STATUS current
    DESCRIPTION "Power supply unit failure"
    ::= { titanEdgeApplianceMonitorAlarmSystemPsuFailureOn 2 }

titanEdgeApplianceMonitorAlarmSystemPsuFailureOffId OBJECT-TYPE
    SYNTAX INTEGER
    MAX-ACCESS read-only
    STATUS current
    DESCRIPTION "."
    ::= { titanEdgeApplianceMonitorAlarmSystemPsuFailureOffMonitors 2 }

titanEdgeDecoderApiLogChannelAddedNotification NOTIFICATION-TYPE
    OBJECTS {
        titanEdgeDecoderApiLogChannelAddedId
    }
    STATUS current
    DESCRIPTION "Channel added"
    ::= { titanEdgeDecoderApiLogs 4 }

titanEdgeDecoderApiLogChannelAddedId OBJECT-TYPE
    SYNTAX DisplayString
    MAX-ACCESS read-only
    STATUS current
    DESCRIPTION "."
    ::= { titanEdgeDecoderApiLogs 4 2 }

titanEdgeDecoderApiLogChannelDeletedNotification NOTIFICATION-TYPE
    OBJECTS {
        titanEdgeDecoderApiLogChannelDeletedId
    }
    STATUS current
    DESCRIPTION "Channel deleted"
    ::= { titanEdgeDecoderApiLogs 5 }

titanEdgeDecoderApiLogChannelDeletedId OBJECT-TYPE
    SYNTAX DisplayString
    MAX-ACCESS read-only
    STATUS current
    DESCRIPTION "."
    ::= { titanEdgeDecoderApiLogs 5 2 }

titanEdgeDecoderApiLogChannelModifiedNotification NOTIFICATION-TYPE
    OBJECTS {
        titanEdgeDecoderApiLogChannelModifiedId
    }
    STATUS current
    DESCRIPTION "Channel modified"
    ::= { titanEdgeDecoderApiLogs 6 }

titanEdgeDecoderApiLogChannelModifiedId OBJECT-TYPE
    SYNTAX DisplayString
    MAX-ACCESS read-only
    STATUS current
    DESCRIPTION "."
    ::= { titanEdgeDecoderApiLogs 6 2 }

titanEdgeDecoderSchedulerLogChannelStartedNotification NOTIFICATION-TYPE
    OBJECTS {
        titanEdgeDecoderSchedulerLogChannelStartedId
    }
    STATUS current
    DESCRIPTION "Channel started"
    ::= { titanEdgeDecoderSchedulerLogs 7 }

titanEdgeDecoderSchedulerLogChannelStartedId OBJECT-TYPE
    SYNTAX DisplayString
    MAX-ACCESS read-only
    STATUS current
    DESCRIPTION "."
    ::= { titanEdgeDecoderSchedulerLogs 7 2 }

titanEdgeDecoderSchedulerLogChannelStoppedNotification NOTIFICATION-TYPE
    OBJECTS {
        titanEdgeDecoderSchedulerLogChannelStoppedId
    }
    STATUS current
    DESCRIPTION "Channel stopped"
    ::= { titanEdgeDecoderSchedulerLogs 8 }

titanEdgeDecoderSchedulerLogChannelStoppedId OBJECT-TYPE
    SYNTAX DisplayString
    MAX-ACCESS read-only
    STATUS current
    DESCRIPTION "."
    ::= { titanEdgeDecoderSchedulerLogs 8 2 }

titanEdgeDecoderSchedulerLogChannelFailoverInputChangedNotification NOTIFICATION-TYPE
    OBJECTS {
        titanEdgeDecoderSchedulerLogChannelFailoverInputChangedId,
        titanEdgeDecoderSchedulerLogChannelFailoverInputChangedIndex
    }
    STATUS current
    DESCRIPTION "Channel failover input changed"
    ::= { titanEdgeDecoderSchedulerLogs 10 }

titanEdgeDecoderSchedulerLogChannelFailoverInputChangedId OBJECT-TYPE
    SYNTAX DisplayString
    MAX-ACCESS read-only
    STATUS current
    DESCRIPTION "."
    ::= { titanEdgeDecoderSchedulerLogs 10 2 }

titanEdgeDecoderSchedulerLogChannelFailoverInputChangedIndex OBJECT-TYPE
    SYNTAX DisplayString
    MAX-ACCESS read-only
    STATUS current
    DESCRIPTION "."
    ::= { titanEdgeDecoderSchedulerLogs 10 2 }

titanEdgeDecoderSchedulerLogOutputSplicingInProgressNotification NOTIFICATION-TYPE
    OBJECTS {
        titanEdgeDecoderSchedulerLogOutputSplicingInProgressId
    }
    STATUS current
    DESCRIPTION "Splicing in progress"
    ::= { titanEdgeDecoderSchedulerLogs 17 }

titanEdgeDecoderSchedulerLogOutputSplicingInProgressId OBJECT-TYPE
    SYNTAX DisplayString
    MAX-ACCESS read-only
    STATUS current
    DESCRIPTION "."
    ::= { titanEdgeDecoderSchedulerLogs 17 2 }

titanEdgeDecoderSchedulerLogOutputSplicingDoneNotification NOTIFICATION-TYPE
    OBJECTS {
        titanEdgeDecoderSchedulerLogOutputSplicingDoneId,
        titanEdgeDecoderSchedulerLogOutputSplicingDoneReason
    }
    STATUS current
    DESCRIPTION "Splicing is done"
    ::= { titanEdgeDecoderSchedulerLogs 18 }

titanEdgeDecoderSchedulerLogOutputSplicingDoneId OBJECT-TYPE
    SYNTAX DisplayString
    MAX-ACCESS read-only
    STATUS current
    DESCRIPTION "."
    ::= { titanEdgeDecoderSchedulerLogs 18 2 }

titanEdgeDecoderSchedulerLogOutputSplicingDoneReason OBJECT-TYPE
    SYNTAX DisplayString
    MAX-ACCESS read-only
    STATUS current
    DESCRIPTION "."
    ::= { titanEdgeDecoderSchedulerLogs 18 2 }

titanEdgeDecoderSchedulerAlarmTsInputSignalMissingOnNotification NOTIFICATION-TYPE
    OBJECTS {
        titanEdgeDecoderSchedulerAlarmTsInputSignalMissingOnId,
        titanEdgeDecoderSchedulerAlarmTsInputSignalMissingOnIndex
    }
    STATUS current
    DESCRIPTION "TS input signal missing"
    ::= { titanEdgeDecoderSchedulerAlarmTsInputSignalMissingOn 1 }

titanEdgeDecoderSchedulerAlarmTsInputSignalMissingOnId OBJECT-TYPE
    SYNTAX DisplayString
    MAX-ACCESS read-only
    STATUS current
    DESCRIPTION "."
    ::= { titanEdgeDecoderSchedulerAlarmTsInputSignalMissingOn 1 2 }

titanEdgeDecoderSchedulerAlarmTsInputSignalMissingOnIndex OBJECT-TYPE
    SYNTAX DisplayString
    MAX-ACCESS read-only
    STATUS current
    DESCRIPTION "."
    ::= { titanEdgeDecoderSchedulerAlarmTsInputSignalMissingOn 1 2 }

titanEdgeDecoderSchedulerAlarmTsInputSignalMissingOffNotification NOTIFICATION-TYPE
    OBJECTS {
        titanEdgeDecoderSchedulerAlarmTsInputSignalMissingOffId,
        titanEdgeDecoderSchedulerAlarmTsInputSignalMissingOffIndex
    }
    STATUS current
    DESCRIPTION "TS input signal missing"
    ::= { titanEdgeDecoderSchedulerAlarmTsInputSignalMissingOn 2 }

titanEdgeDecoderSchedulerAlarmTsInputSignalMissingOffId OBJECT-TYPE
    SYNTAX DisplayString
    MAX-ACCESS read-only
    STATUS current
    DESCRIPTION "."
    ::= { titanEdgeDecoderSchedulerAlarmTsInputSignalMissingOffMonitors 2 }

titanEdgeDecoderSchedulerAlarmTsInputSignalMissingOffIndex OBJECT-TYPE
    SYNTAX DisplayString
    MAX-ACCESS read-only
    STATUS current
    DESCRIPTION "."
    ::= { titanEdgeDecoderSchedulerAlarmTsInputSignalMissingOffMonitors 2 }

titanEdgeDecoderSchedulerAlarmSatelliteInputSignalNotLockedOnNotification NOTIFICATION-TYPE
    OBJECTS {
        titanEdgeDecoderSchedulerAlarmSatelliteInputSignalNotLockedOnId,
        titanEdgeDecoderSchedulerAlarmSatelliteInputSignalNotLockedOnIndex
    }
    STATUS current
    DESCRIPTION "Satellite input signal not locked"
    ::= { titanEdgeDecoderSchedulerAlarmSatelliteInputSignalNotLockedOn 1 }

titanEdgeDecoderSchedulerAlarmSatelliteInputSignalNotLockedOnId OBJECT-TYPE
    SYNTAX DisplayString
    MAX-ACCESS read-only
    STATUS current
    DESCRIPTION "."
    ::= { titanEdgeDecoderSchedulerAlarmSatelliteInputSignalNotLockedOn 1 2 }

titanEdgeDecoderSchedulerAlarmSatelliteInputSignalNotLockedOnIndex OBJECT-TYPE
    SYNTAX DisplayString
    MAX-ACCESS read-only
    STATUS current
    DESCRIPTION "."
    ::= { titanEdgeDecoderSchedulerAlarmSatelliteInputSignalNotLockedOn 1 2 }

titanEdgeDecoderSchedulerAlarmSatelliteInputSignalNotLockedOffNotification NOTIFICATION-TYPE
    OBJECTS {
        titanEdgeDecoderSchedulerAlarmSatelliteInputSignalNotLockedOffId,
        titanEdgeDecoderSchedulerAlarmSatelliteInputSignalNotLockedOffIndex
    }
    STATUS current
    DESCRIPTION "Satellite input signal not locked"
    ::= { titanEdgeDecoderSchedulerAlarmSatelliteInputSignalNotLockedOn 2 }

titanEdgeDecoderSchedulerAlarmSatelliteInputSignalNotLockedOffId OBJECT-TYPE
    SYNTAX DisplayString
    MAX-ACCESS read-only
    STATUS current
    DESCRIPTION "."
    ::= { titanEdgeDecoderSchedulerAlarmSatelliteInputSignalNotLockedOffMonitors 2 }

titanEdgeDecoderSchedulerAlarmSatelliteInputSignalNotLockedOffIndex OBJECT-TYPE
    SYNTAX DisplayString
    MAX-ACCESS read-only
    STATUS current
    DESCRIPTION "."
    ::= { titanEdgeDecoderSchedulerAlarmSatelliteInputSignalNotLockedOffMonitors 2 }

titanEdgeDecoderSchedulerAlarmZixiInputNotConnectedOnNotification NOTIFICATION-TYPE
    OBJECTS {
        titanEdgeDecoderSchedulerAlarmZixiInputNotConnectedOnId,
        titanEdgeDecoderSchedulerAlarmZixiInputNotConnectedOnIndex
    }
    STATUS current
    DESCRIPTION "Zixi input not connected"
    ::= { titanEdgeDecoderSchedulerAlarmZixiInputNotConnectedOn 1 }

titanEdgeDecoderSchedulerAlarmZixiInputNotConnectedOnId OBJECT-TYPE
    SYNTAX DisplayString
    MAX-ACCESS read-only
    STATUS current
    DESCRIPTION "."
    ::= { titanEdgeDecoderSchedulerAlarmZixiInputNotConnectedOn 1 2 }

titanEdgeDecoderSchedulerAlarmZixiInputNotConnectedOnIndex OBJECT-TYPE
    SYNTAX DisplayString
    MAX-ACCESS read-only
    STATUS current
    DESCRIPTION "."
    ::= { titanEdgeDecoderSchedulerAlarmZixiInputNotConnectedOn 1 2 }

titanEdgeDecoderSchedulerAlarmZixiInputNotConnectedOffNotification NOTIFICATION-TYPE
    OBJECTS {
        titanEdgeDecoderSchedulerAlarmZixiInputNotConnectedOffId,
        titanEdgeDecoderSchedulerAlarmZixiInputNotConnectedOffIndex
    }
    STATUS current
    DESCRIPTION "Zixi input not connected"
    ::= { titanEdgeDecoderSchedulerAlarmZixiInputNotConnectedOn 2 }

titanEdgeDecoderSchedulerAlarmZixiInputNotConnectedOffId OBJECT-TYPE
    SYNTAX DisplayString
    MAX-ACCESS read-only
    STATUS current
    DESCRIPTION "."
    ::= { titanEdgeDecoderSchedulerAlarmZixiInputNotConnectedOffMonitors 2 }

titanEdgeDecoderSchedulerAlarmZixiInputNotConnectedOffIndex OBJECT-TYPE
    SYNTAX DisplayString
    MAX-ACCESS read-only
    STATUS current
    DESCRIPTION "."
    ::= { titanEdgeDecoderSchedulerAlarmZixiInputNotConnectedOffMonitors 2 }

titanEdgeDecoderSchedulerAlarmZixiExcessiveJitterOnNotification NOTIFICATION-TYPE
    OBJECTS {
        titanEdgeDecoderSchedulerAlarmZixiExcessiveJitterOnId,
        titanEdgeDecoderSchedulerAlarmZixiExcessiveJitterOnIndex,
        titanEdgeDecoderSchedulerAlarmZixiExcessiveJitterOnThreshold
    }
    STATUS current
    DESCRIPTION "Excessive Zixi input jitter"
    ::= { titanEdgeDecoderSchedulerAlarmZixiExcessiveJitterOn 1 }

titanEdgeDecoderSchedulerAlarmZixiExcessiveJitterOnId OBJECT-TYPE
    SYNTAX DisplayString
    MAX-ACCESS read-only
    STATUS current
    DESCRIPTION "."
    ::= { titanEdgeDecoderSchedulerAlarmZixiExcessiveJitterOn 1 2 }

titanEdgeDecoderSchedulerAlarmZixiExcessiveJitterOnIndex OBJECT-TYPE
    SYNTAX DisplayString
    MAX-ACCESS read-only
    STATUS current
    DESCRIPTION "."
    ::= { titanEdgeDecoderSchedulerAlarmZixiExcessiveJitterOn 1 2 }

titanEdgeDecoderSchedulerAlarmZixiExcessiveJitterOnThreshold OBJECT-TYPE
    SYNTAX INTEGER
    MAX-ACCESS read-only
    STATUS current
    DESCRIPTION "."
    ::= { titanEdgeDecoderSchedulerAlarmZixiExcessiveJitterOn 1 3 }

titanEdgeDecoderSchedulerAlarmZixiExcessiveJitterOffNotification NOTIFICATION-TYPE
    OBJECTS {
        titanEdgeDecoderSchedulerAlarmZixiExcessiveJitterOffId,
        titanEdgeDecoderSchedulerAlarmZixiExcessiveJitterOffIndex,
        titanEdgeDecoderSchedulerAlarmZixiExcessiveJitterOffThreshold
    }
    STATUS current
    DESCRIPTION "Excessive Zixi input jitter"
    ::= { titanEdgeDecoderSchedulerAlarmZixiExcessiveJitterOn 2 }

titanEdgeDecoderSchedulerAlarmZixiExcessiveJitterOffId OBJECT-TYPE
    SYNTAX DisplayString
    MAX-ACCESS read-only
    STATUS current
    DESCRIPTION "."
    ::= { titanEdgeDecoderSchedulerAlarmZixiExcessiveJitterOffMonitors 2 }

titanEdgeDecoderSchedulerAlarmZixiExcessiveJitterOffIndex OBJECT-TYPE
    SYNTAX DisplayString
    MAX-ACCESS read-only
    STATUS current
    DESCRIPTION "."
    ::= { titanEdgeDecoderSchedulerAlarmZixiExcessiveJitterOffMonitors 2 }

titanEdgeDecoderSchedulerAlarmZixiExcessiveJitterOffThreshold OBJECT-TYPE
    SYNTAX INTEGER
    MAX-ACCESS read-only
    STATUS current
    DESCRIPTION "."
    ::= { titanEdgeDecoderSchedulerAlarmZixiExcessiveJitterOffMonitors 3 }

titanEdgeDecoderSchedulerAlarmCompositionProgramMissingOnNotification NOTIFICATION-TYPE
    OBJECTS {
        titanEdgeDecoderSchedulerAlarmCompositionProgramMissingOnId
    }
    STATUS current
    DESCRIPTION "Program missing"
    ::= { titanEdgeDecoderSchedulerAlarmCompositionProgramMissingOn 1 }

titanEdgeDecoderSchedulerAlarmCompositionProgramMissingOnId OBJECT-TYPE
    SYNTAX DisplayString
    MAX-ACCESS read-only
    STATUS current
    DESCRIPTION "."
    ::= { titanEdgeDecoderSchedulerAlarmCompositionProgramMissingOn 1 2 }

titanEdgeDecoderSchedulerAlarmCompositionProgramMissingOffNotification NOTIFICATION-TYPE
    OBJECTS {
        titanEdgeDecoderSchedulerAlarmCompositionProgramMissingOffId
    }
    STATUS current
    DESCRIPTION "Program missing"
    ::= { titanEdgeDecoderSchedulerAlarmCompositionProgramMissingOn 2 }

titanEdgeDecoderSchedulerAlarmCompositionProgramMissingOffId OBJECT-TYPE
    SYNTAX DisplayString
    MAX-ACCESS read-only
    STATUS current
    DESCRIPTION "."
    ::= { titanEdgeDecoderSchedulerAlarmCompositionProgramMissingOffMonitors 2 }

titanEdgeDecoderSchedulerAlarmCompositionProgramScrambledOnNotification NOTIFICATION-TYPE
    OBJECTS {
        titanEdgeDecoderSchedulerAlarmCompositionProgramScrambledOnId
    }
    STATUS current
    DESCRIPTION "Program scrambled"
    ::= { titanEdgeDecoderSchedulerAlarmCompositionProgramScrambledOn 1 }

titanEdgeDecoderSchedulerAlarmCompositionProgramScrambledOnId OBJECT-TYPE
    SYNTAX DisplayString
    MAX-ACCESS read-only
    STATUS current
    DESCRIPTION "."
    ::= { titanEdgeDecoderSchedulerAlarmCompositionProgramScrambledOn 1 2 }

titanEdgeDecoderSchedulerAlarmCompositionProgramScrambledOffNotification NOTIFICATION-TYPE
    OBJECTS {
        titanEdgeDecoderSchedulerAlarmCompositionProgramScrambledOffId
    }
    STATUS current
    DESCRIPTION "Program scrambled"
    ::= { titanEdgeDecoderSchedulerAlarmCompositionProgramScrambledOn 2 }

titanEdgeDecoderSchedulerAlarmCompositionProgramScrambledOffId OBJECT-TYPE
    SYNTAX DisplayString
    MAX-ACCESS read-only
    STATUS current
    DESCRIPTION "."
    ::= { titanEdgeDecoderSchedulerAlarmCompositionProgramScrambledOffMonitors 2 }

titanEdgeDecoderSchedulerAlarmCompositionVideoSourceMissingOnNotification NOTIFICATION-TYPE
    OBJECTS {
        titanEdgeDecoderSchedulerAlarmCompositionVideoSourceMissingOnId
    }
    STATUS current
    DESCRIPTION "Video source missing"
    ::= { titanEdgeDecoderSchedulerAlarmCompositionVideoSourceMissingOn 1 }

titanEdgeDecoderSchedulerAlarmCompositionVideoSourceMissingOnId OBJECT-TYPE
    SYNTAX DisplayString
    MAX-ACCESS read-only
    STATUS current
    DESCRIPTION "."
    ::= { titanEdgeDecoderSchedulerAlarmCompositionVideoSourceMissingOn 1 2 }

titanEdgeDecoderSchedulerAlarmCompositionVideoSourceMissingOffNotification NOTIFICATION-TYPE
    OBJECTS {
        titanEdgeDecoderSchedulerAlarmCompositionVideoSourceMissingOffId
    }
    STATUS current
    DESCRIPTION "Video source missing"
    ::= { titanEdgeDecoderSchedulerAlarmCompositionVideoSourceMissingOn 2 }

titanEdgeDecoderSchedulerAlarmCompositionVideoSourceMissingOffId OBJECT-TYPE
    SYNTAX DisplayString
    MAX-ACCESS read-only
    STATUS current
    DESCRIPTION "."
    ::= { titanEdgeDecoderSchedulerAlarmCompositionVideoSourceMissingOffMonitors 2 }

titanEdgeDecoderSchedulerAlarmCompositionAudioSourceMissingOnNotification NOTIFICATION-TYPE
    OBJECTS {
        titanEdgeDecoderSchedulerAlarmCompositionAudioSourceMissingOnId,
        titanEdgeDecoderSchedulerAlarmCompositionAudioSourceMissingOnIndex
    }
    STATUS current
    DESCRIPTION "Audio source missing"
    ::= { titanEdgeDecoderSchedulerAlarmCompositionAudioSourceMissingOn 1 }

titanEdgeDecoderSchedulerAlarmCompositionAudioSourceMissingOnId OBJECT-TYPE
    SYNTAX DisplayString
    MAX-ACCESS read-only
    STATUS current
    DESCRIPTION "."
    ::= { titanEdgeDecoderSchedulerAlarmCompositionAudioSourceMissingOn 1 2 }

titanEdgeDecoderSchedulerAlarmCompositionAudioSourceMissingOnIndex OBJECT-TYPE
    SYNTAX DisplayString
    MAX-ACCESS read-only
    STATUS current
    DESCRIPTION "."
    ::= { titanEdgeDecoderSchedulerAlarmCompositionAudioSourceMissingOn 1 2 }

titanEdgeDecoderSchedulerAlarmCompositionAudioSourceMissingOffNotification NOTIFICATION-TYPE
    OBJECTS {
        titanEdgeDecoderSchedulerAlarmCompositionAudioSourceMissingOffId,
        titanEdgeDecoderSchedulerAlarmCompositionAudioSourceMissingOffIndex
    }
    STATUS current
    DESCRIPTION "Audio source missing"
    ::= { titanEdgeDecoderSchedulerAlarmCompositionAudioSourceMissingOn 2 }

titanEdgeDecoderSchedulerAlarmCompositionAudioSourceMissingOffId OBJECT-TYPE
    SYNTAX DisplayString
    MAX-ACCESS read-only
    STATUS current
    DESCRIPTION "."
    ::= { titanEdgeDecoderSchedulerAlarmCompositionAudioSourceMissingOffMonitors 2 }

titanEdgeDecoderSchedulerAlarmCompositionAudioSourceMissingOffIndex OBJECT-TYPE
    SYNTAX DisplayString
    MAX-ACCESS read-only
    STATUS current
    DESCRIPTION "."
    ::= { titanEdgeDecoderSchedulerAlarmCompositionAudioSourceMissingOffMonitors 2 }

titanEdgeDecoderSchedulerAlarmCompositionDataSourceMissingOnNotification NOTIFICATION-TYPE
    OBJECTS {
        titanEdgeDecoderSchedulerAlarmCompositionDataSourceMissingOnId,
        titanEdgeDecoderSchedulerAlarmCompositionDataSourceMissingOnIndex
    }
    STATUS current
    DESCRIPTION "Data source missing"
    ::= { titanEdgeDecoderSchedulerAlarmCompositionDataSourceMissingOn 1 }

titanEdgeDecoderSchedulerAlarmCompositionDataSourceMissingOnId OBJECT-TYPE
    SYNTAX DisplayString
    MAX-ACCESS read-only
    STATUS current
    DESCRIPTION "."
    ::= { titanEdgeDecoderSchedulerAlarmCompositionDataSourceMissingOn 1 2 }

titanEdgeDecoderSchedulerAlarmCompositionDataSourceMissingOnIndex OBJECT-TYPE
    SYNTAX DisplayString
    MAX-ACCESS read-only
    STATUS current
    DESCRIPTION "."
    ::= { titanEdgeDecoderSchedulerAlarmCompositionDataSourceMissingOn 1 2 }

titanEdgeDecoderSchedulerAlarmCompositionDataSourceMissingOffNotification NOTIFICATION-TYPE
    OBJECTS {
        titanEdgeDecoderSchedulerAlarmCompositionDataSourceMissingOffId,
        titanEdgeDecoderSchedulerAlarmCompositionDataSourceMissingOffIndex
    }
    STATUS current
    DESCRIPTION "Data source missing"
    ::= { titanEdgeDecoderSchedulerAlarmCompositionDataSourceMissingOn 2 }

titanEdgeDecoderSchedulerAlarmCompositionDataSourceMissingOffId OBJECT-TYPE
    SYNTAX DisplayString
    MAX-ACCESS read-only
    STATUS current
    DESCRIPTION "."
    ::= { titanEdgeDecoderSchedulerAlarmCompositionDataSourceMissingOffMonitors 2 }

titanEdgeDecoderSchedulerAlarmCompositionDataSourceMissingOffIndex OBJECT-TYPE
    SYNTAX DisplayString
    MAX-ACCESS read-only
    STATUS current
    DESCRIPTION "."
    ::= { titanEdgeDecoderSchedulerAlarmCompositionDataSourceMissingOffMonitors 2 }

titanEdgeDecoderSchedulerAlarmLicenseMissingOnNotification NOTIFICATION-TYPE
    OBJECTS {
        titanEdgeDecoderSchedulerAlarmLicenseMissingOnId,
        titanEdgeDecoderSchedulerAlarmLicenseMissingOnName
    }
    STATUS current
    DESCRIPTION "License Missing"
    ::= { titanEdgeDecoderSchedulerAlarmLicenseMissingOn 1 }

titanEdgeDecoderSchedulerAlarmLicenseMissingOnId OBJECT-TYPE
    SYNTAX DisplayString
    MAX-ACCESS read-only
    STATUS current
    DESCRIPTION "."
    ::= { titanEdgeDecoderSchedulerAlarmLicenseMissingOn 1 2 }

titanEdgeDecoderSchedulerAlarmLicenseMissingOnName OBJECT-TYPE
    SYNTAX DisplayString
    MAX-ACCESS read-only
    STATUS current
    DESCRIPTION "."
    ::= { titanEdgeDecoderSchedulerAlarmLicenseMissingOn 1 2 }

titanEdgeDecoderSchedulerAlarmLicenseMissingOffNotification NOTIFICATION-TYPE
    OBJECTS {
        titanEdgeDecoderSchedulerAlarmLicenseMissingOffId,
        titanEdgeDecoderSchedulerAlarmLicenseMissingOffName
    }
    STATUS current
    DESCRIPTION "License Missing"
    ::= { titanEdgeDecoderSchedulerAlarmLicenseMissingOn 2 }

titanEdgeDecoderSchedulerAlarmLicenseMissingOffId OBJECT-TYPE
    SYNTAX DisplayString
    MAX-ACCESS read-only
    STATUS current
    DESCRIPTION "."
    ::= { titanEdgeDecoderSchedulerAlarmLicenseMissingOffMonitors 2 }

titanEdgeDecoderSchedulerAlarmLicenseMissingOffName OBJECT-TYPE
    SYNTAX DisplayString
    MAX-ACCESS read-only
    STATUS current
    DESCRIPTION "."
    ::= { titanEdgeDecoderSchedulerAlarmLicenseMissingOffMonitors 2 }

titanEdgeDecoderSchedulerAlarmCompositionProgramDecodingPreventedOnNotification NOTIFICATION-TYPE
    OBJECTS {
        titanEdgeDecoderSchedulerAlarmCompositionProgramDecodingPreventedOnId
    }
    STATUS current
    DESCRIPTION "Program decoding prevented"
    ::= { titanEdgeDecoderSchedulerAlarmCompositionProgramDecodingPreventedOn 1 }

titanEdgeDecoderSchedulerAlarmCompositionProgramDecodingPreventedOnId OBJECT-TYPE
    SYNTAX DisplayString
    MAX-ACCESS read-only
    STATUS current
    DESCRIPTION "."
    ::= { titanEdgeDecoderSchedulerAlarmCompositionProgramDecodingPreventedOn 1 2 }

titanEdgeDecoderSchedulerAlarmCompositionProgramDecodingPreventedOffNotification NOTIFICATION-TYPE
    OBJECTS {
        titanEdgeDecoderSchedulerAlarmCompositionProgramDecodingPreventedOffId
    }
    STATUS current
    DESCRIPTION "Program decoding prevented"
    ::= { titanEdgeDecoderSchedulerAlarmCompositionProgramDecodingPreventedOn 2 }

titanEdgeDecoderSchedulerAlarmCompositionProgramDecodingPreventedOffId OBJECT-TYPE
    SYNTAX DisplayString
    MAX-ACCESS read-only
    STATUS current
    DESCRIPTION "."
    ::= { titanEdgeDecoderSchedulerAlarmCompositionProgramDecodingPreventedOffMonitors 2 }

titanEdgeDecoderSchedulerAlarmCompositionVideoConstraintIncompatibleOnNotification NOTIFICATION-TYPE
    OBJECTS {
        titanEdgeDecoderSchedulerAlarmCompositionVideoConstraintIncompatibleOnId
    }
    STATUS current
    DESCRIPTION "Video constraint incompatible"
    ::= { titanEdgeDecoderSchedulerAlarmCompositionVideoConstraintIncompatibleOn 1 }

titanEdgeDecoderSchedulerAlarmCompositionVideoConstraintIncompatibleOnId OBJECT-TYPE
    SYNTAX DisplayString
    MAX-ACCESS read-only
    STATUS current
    DESCRIPTION "."
    ::= { titanEdgeDecoderSchedulerAlarmCompositionVideoConstraintIncompatibleOn 1 2 }

titanEdgeDecoderSchedulerAlarmCompositionVideoConstraintIncompatibleOffNotification NOTIFICATION-TYPE
    OBJECTS {
        titanEdgeDecoderSchedulerAlarmCompositionVideoConstraintIncompatibleOffId
    }
    STATUS current
    DESCRIPTION "Video constraint incompatible"
    ::= { titanEdgeDecoderSchedulerAlarmCompositionVideoConstraintIncompatibleOn 2 }

titanEdgeDecoderSchedulerAlarmCompositionVideoConstraintIncompatibleOffId OBJECT-TYPE
    SYNTAX DisplayString
    MAX-ACCESS read-only
    STATUS current
    DESCRIPTION "."
    ::= { titanEdgeDecoderSchedulerAlarmCompositionVideoConstraintIncompatibleOffMonitors 2 }

titanEdgeDecoderSchedulerAlarmChannelInternalErrorOnNotification NOTIFICATION-TYPE
    OBJECTS {
        titanEdgeDecoderSchedulerAlarmChannelInternalErrorOnId
    }
    STATUS current
    DESCRIPTION "Channel internal error"
    ::= { titanEdgeDecoderSchedulerAlarmChannelInternalErrorOn 1 }

titanEdgeDecoderSchedulerAlarmChannelInternalErrorOnId OBJECT-TYPE
    SYNTAX DisplayString
    MAX-ACCESS read-only
    STATUS current
    DESCRIPTION "."
    ::= { titanEdgeDecoderSchedulerAlarmChannelInternalErrorOn 1 2 }

titanEdgeDecoderSchedulerAlarmChannelInternalErrorOffNotification NOTIFICATION-TYPE
    OBJECTS {
        titanEdgeDecoderSchedulerAlarmChannelInternalErrorOffId
    }
    STATUS current
    DESCRIPTION "Channel internal error"
    ::= { titanEdgeDecoderSchedulerAlarmChannelInternalErrorOn 2 }

titanEdgeDecoderSchedulerAlarmChannelInternalErrorOffId OBJECT-TYPE
    SYNTAX DisplayString
    MAX-ACCESS read-only
    STATUS current
    DESCRIPTION "."
    ::= { titanEdgeDecoderSchedulerAlarmChannelInternalErrorOffMonitors 2 }

titanEdgeDecoderSchedulerAlarmSdiOutputInvalidTimecodeOffsetOnNotification NOTIFICATION-TYPE
    OBJECTS {
        titanEdgeDecoderSchedulerAlarmSdiOutputInvalidTimecodeOffsetOnId,
        titanEdgeDecoderSchedulerAlarmSdiOutputInvalidTimecodeOffsetOnIndex
    }
    STATUS current
    DESCRIPTION "No timecode in input stream or invalid timecode offset"
    ::= { titanEdgeDecoderSchedulerAlarmSdiOutputInvalidTimecodeOffsetOn 1 }

titanEdgeDecoderSchedulerAlarmSdiOutputInvalidTimecodeOffsetOnId OBJECT-TYPE
    SYNTAX DisplayString
    MAX-ACCESS read-only
    STATUS current
    DESCRIPTION "."
    ::= { titanEdgeDecoderSchedulerAlarmSdiOutputInvalidTimecodeOffsetOn 1 2 }

titanEdgeDecoderSchedulerAlarmSdiOutputInvalidTimecodeOffsetOnIndex OBJECT-TYPE
    SYNTAX DisplayString
    MAX-ACCESS read-only
    STATUS current
    DESCRIPTION "."
    ::= { titanEdgeDecoderSchedulerAlarmSdiOutputInvalidTimecodeOffsetOn 1 2 }

titanEdgeDecoderSchedulerAlarmSdiOutputInvalidTimecodeOffsetOffNotification NOTIFICATION-TYPE
    OBJECTS {
        titanEdgeDecoderSchedulerAlarmSdiOutputInvalidTimecodeOffsetOffId,
        titanEdgeDecoderSchedulerAlarmSdiOutputInvalidTimecodeOffsetOffIndex
    }
    STATUS current
    DESCRIPTION "No timecode in input stream or invalid timecode offset"
    ::= { titanEdgeDecoderSchedulerAlarmSdiOutputInvalidTimecodeOffsetOn 2 }

titanEdgeDecoderSchedulerAlarmSdiOutputInvalidTimecodeOffsetOffId OBJECT-TYPE
    SYNTAX DisplayString
    MAX-ACCESS read-only
    STATUS current
    DESCRIPTION "."
    ::= { titanEdgeDecoderSchedulerAlarmSdiOutputInvalidTimecodeOffsetOffMonitors 2 }

titanEdgeDecoderSchedulerAlarmSdiOutputInvalidTimecodeOffsetOffIndex OBJECT-TYPE
    SYNTAX DisplayString
    MAX-ACCESS read-only
    STATUS current
    DESCRIPTION "."
    ::= { titanEdgeDecoderSchedulerAlarmSdiOutputInvalidTimecodeOffsetOffMonitors 2 }

titanEdgeDecoderSchedulerAlarmSystemExtensionPinUnknownOnNotification NOTIFICATION-TYPE
    OBJECTS {
        titanEdgeDecoderSchedulerAlarmSystemExtensionPinUnknownOnId,
        titanEdgeDecoderSchedulerAlarmSystemExtensionPinUnknownOnIndex
    }
    STATUS current
    DESCRIPTION "Hardware extension pin unknown"
    ::= { titanEdgeDecoderSchedulerAlarmSystemExtensionPinUnknownOn 1 }

titanEdgeDecoderSchedulerAlarmSystemExtensionPinUnknownOnId OBJECT-TYPE
    SYNTAX DisplayString
    MAX-ACCESS read-only
    STATUS current
    DESCRIPTION "."
    ::= { titanEdgeDecoderSchedulerAlarmSystemExtensionPinUnknownOn 1 2 }

titanEdgeDecoderSchedulerAlarmSystemExtensionPinUnknownOnIndex OBJECT-TYPE
    SYNTAX DisplayString
    MAX-ACCESS read-only
    STATUS current
    DESCRIPTION "."
    ::= { titanEdgeDecoderSchedulerAlarmSystemExtensionPinUnknownOn 1 2 }

titanEdgeDecoderSchedulerAlarmSystemExtensionPinUnknownOffNotification NOTIFICATION-TYPE
    OBJECTS {
        titanEdgeDecoderSchedulerAlarmSystemExtensionPinUnknownOffId,
        titanEdgeDecoderSchedulerAlarmSystemExtensionPinUnknownOffIndex
    }
    STATUS current
    DESCRIPTION "Hardware extension pin unknown"
    ::= { titanEdgeDecoderSchedulerAlarmSystemExtensionPinUnknownOn 2 }

titanEdgeDecoderSchedulerAlarmSystemExtensionPinUnknownOffId OBJECT-TYPE
    SYNTAX DisplayString
    MAX-ACCESS read-only
    STATUS current
    DESCRIPTION "."
    ::= { titanEdgeDecoderSchedulerAlarmSystemExtensionPinUnknownOffMonitors 2 }

titanEdgeDecoderSchedulerAlarmSystemExtensionPinUnknownOffIndex OBJECT-TYPE
    SYNTAX DisplayString
    MAX-ACCESS read-only
    STATUS current
    DESCRIPTION "."
    ::= { titanEdgeDecoderSchedulerAlarmSystemExtensionPinUnknownOffMonitors 2 }

titanEdgeDecoderSchedulerAlarmSdiOutputGenlockUnlockedOnNotification NOTIFICATION-TYPE
    OBJECTS {
        titanEdgeDecoderSchedulerAlarmSdiOutputGenlockUnlockedOnId,
        titanEdgeDecoderSchedulerAlarmSdiOutputGenlockUnlockedOnIndex
    }
    STATUS current
    DESCRIPTION "SDI output genlock unlocked"
    ::= { titanEdgeDecoderSchedulerAlarmSdiOutputGenlockUnlockedOn 1 }

titanEdgeDecoderSchedulerAlarmSdiOutputGenlockUnlockedOnId OBJECT-TYPE
    SYNTAX DisplayString
    MAX-ACCESS read-only
    STATUS current
    DESCRIPTION "."
    ::= { titanEdgeDecoderSchedulerAlarmSdiOutputGenlockUnlockedOn 1 2 }

titanEdgeDecoderSchedulerAlarmSdiOutputGenlockUnlockedOnIndex OBJECT-TYPE
    SYNTAX DisplayString
    MAX-ACCESS read-only
    STATUS current
    DESCRIPTION "."
    ::= { titanEdgeDecoderSchedulerAlarmSdiOutputGenlockUnlockedOn 1 2 }

titanEdgeDecoderSchedulerAlarmSdiOutputGenlockUnlockedOffNotification NOTIFICATION-TYPE
    OBJECTS {
        titanEdgeDecoderSchedulerAlarmSdiOutputGenlockUnlockedOffId,
        titanEdgeDecoderSchedulerAlarmSdiOutputGenlockUnlockedOffIndex
    }
    STATUS current
    DESCRIPTION "SDI output genlock unlocked"
    ::= { titanEdgeDecoderSchedulerAlarmSdiOutputGenlockUnlockedOn 2 }

titanEdgeDecoderSchedulerAlarmSdiOutputGenlockUnlockedOffId OBJECT-TYPE
    SYNTAX DisplayString
    MAX-ACCESS read-only
    STATUS current
    DESCRIPTION "."
    ::= { titanEdgeDecoderSchedulerAlarmSdiOutputGenlockUnlockedOffMonitors 2 }

titanEdgeDecoderSchedulerAlarmSdiOutputGenlockUnlockedOffIndex OBJECT-TYPE
    SYNTAX DisplayString
    MAX-ACCESS read-only
    STATUS current
    DESCRIPTION "."
    ::= { titanEdgeDecoderSchedulerAlarmSdiOutputGenlockUnlockedOffMonitors 2 }

titanEdgeDecoderSchedulerAlarmSystemExtensionPinInConflictOnNotification NOTIFICATION-TYPE
    OBJECTS {
        titanEdgeDecoderSchedulerAlarmSystemExtensionPinInConflictOnId,
        titanEdgeDecoderSchedulerAlarmSystemExtensionPinInConflictOnIndex
    }
    STATUS current
    DESCRIPTION "Hardware extension pin in conflict"
    ::= { titanEdgeDecoderSchedulerAlarmSystemExtensionPinInConflictOn 1 }

titanEdgeDecoderSchedulerAlarmSystemExtensionPinInConflictOnId OBJECT-TYPE
    SYNTAX DisplayString
    MAX-ACCESS read-only
    STATUS current
    DESCRIPTION "."
    ::= { titanEdgeDecoderSchedulerAlarmSystemExtensionPinInConflictOn 1 2 }

titanEdgeDecoderSchedulerAlarmSystemExtensionPinInConflictOnIndex OBJECT-TYPE
    SYNTAX DisplayString
    MAX-ACCESS read-only
    STATUS current
    DESCRIPTION "."
    ::= { titanEdgeDecoderSchedulerAlarmSystemExtensionPinInConflictOn 1 2 }

titanEdgeDecoderSchedulerAlarmSystemExtensionPinInConflictOffNotification NOTIFICATION-TYPE
    OBJECTS {
        titanEdgeDecoderSchedulerAlarmSystemExtensionPinInConflictOffId,
        titanEdgeDecoderSchedulerAlarmSystemExtensionPinInConflictOffIndex
    }
    STATUS current
    DESCRIPTION "Hardware extension pin in conflict"
    ::= { titanEdgeDecoderSchedulerAlarmSystemExtensionPinInConflictOn 2 }

titanEdgeDecoderSchedulerAlarmSystemExtensionPinInConflictOffId OBJECT-TYPE
    SYNTAX DisplayString
    MAX-ACCESS read-only
    STATUS current
    DESCRIPTION "."
    ::= { titanEdgeDecoderSchedulerAlarmSystemExtensionPinInConflictOffMonitors 2 }

titanEdgeDecoderSchedulerAlarmSystemExtensionPinInConflictOffIndex OBJECT-TYPE
    SYNTAX DisplayString
    MAX-ACCESS read-only
    STATUS current
    DESCRIPTION "."
    ::= { titanEdgeDecoderSchedulerAlarmSystemExtensionPinInConflictOffMonitors 2 }

titanEdgeDecoderSchedulerAlarmSystemExtensionPinConfigurationInvalidOnNotification NOTIFICATION-TYPE
    OBJECTS {
        titanEdgeDecoderSchedulerAlarmSystemExtensionPinConfigurationInvalidOnId,
        titanEdgeDecoderSchedulerAlarmSystemExtensionPinConfigurationInvalidOnIndex
    }
    STATUS current
    DESCRIPTION "Hardware extension pin configuration invalid"
    ::= { titanEdgeDecoderSchedulerAlarmSystemExtensionPinConfigurationInvalidOn 1 }

titanEdgeDecoderSchedulerAlarmSystemExtensionPinConfigurationInvalidOnId OBJECT-TYPE
    SYNTAX DisplayString
    MAX-ACCESS read-only
    STATUS current
    DESCRIPTION "."
    ::= { titanEdgeDecoderSchedulerAlarmSystemExtensionPinConfigurationInvalidOn 1 2 }

titanEdgeDecoderSchedulerAlarmSystemExtensionPinConfigurationInvalidOnIndex OBJECT-TYPE
    SYNTAX DisplayString
    MAX-ACCESS read-only
    STATUS current
    DESCRIPTION "."
    ::= { titanEdgeDecoderSchedulerAlarmSystemExtensionPinConfigurationInvalidOn 1 2 }

titanEdgeDecoderSchedulerAlarmSystemExtensionPinConfigurationInvalidOffNotification NOTIFICATION-TYPE
    OBJECTS {
        titanEdgeDecoderSchedulerAlarmSystemExtensionPinConfigurationInvalidOffId,
        titanEdgeDecoderSchedulerAlarmSystemExtensionPinConfigurationInvalidOffIndex
    }
    STATUS current
    DESCRIPTION "Hardware extension pin configuration invalid"
    ::= { titanEdgeDecoderSchedulerAlarmSystemExtensionPinConfigurationInvalidOn 2 }

titanEdgeDecoderSchedulerAlarmSystemExtensionPinConfigurationInvalidOffId OBJECT-TYPE
    SYNTAX DisplayString
    MAX-ACCESS read-only
    STATUS current
    DESCRIPTION "."
    ::= { titanEdgeDecoderSchedulerAlarmSystemExtensionPinConfigurationInvalidOffMonitors 2 }

titanEdgeDecoderSchedulerAlarmSystemExtensionPinConfigurationInvalidOffIndex OBJECT-TYPE
    SYNTAX DisplayString
    MAX-ACCESS read-only
    STATUS current
    DESCRIPTION "."
    ::= { titanEdgeDecoderSchedulerAlarmSystemExtensionPinConfigurationInvalidOffMonitors 2 }

titanEdgeDecoderSchedulerAlarmInternalInputNotConnectedOnNotification NOTIFICATION-TYPE
    OBJECTS {
        titanEdgeDecoderSchedulerAlarmInternalInputNotConnectedOnId,
        titanEdgeDecoderSchedulerAlarmInternalInputNotConnectedOnIndex
    }
    STATUS current
    DESCRIPTION "Internal input not connected"
    ::= { titanEdgeDecoderSchedulerAlarmInternalInputNotConnectedOn 1 }

titanEdgeDecoderSchedulerAlarmInternalInputNotConnectedOnId OBJECT-TYPE
    SYNTAX DisplayString
    MAX-ACCESS read-only
    STATUS current
    DESCRIPTION "."
    ::= { titanEdgeDecoderSchedulerAlarmInternalInputNotConnectedOn 1 2 }

titanEdgeDecoderSchedulerAlarmInternalInputNotConnectedOnIndex OBJECT-TYPE
    SYNTAX DisplayString
    MAX-ACCESS read-only
    STATUS current
    DESCRIPTION "."
    ::= { titanEdgeDecoderSchedulerAlarmInternalInputNotConnectedOn 1 2 }

titanEdgeDecoderSchedulerAlarmInternalInputNotConnectedOffNotification NOTIFICATION-TYPE
    OBJECTS {
        titanEdgeDecoderSchedulerAlarmInternalInputNotConnectedOffId,
        titanEdgeDecoderSchedulerAlarmInternalInputNotConnectedOffIndex
    }
    STATUS current
    DESCRIPTION "Internal input not connected"
    ::= { titanEdgeDecoderSchedulerAlarmInternalInputNotConnectedOn 2 }

titanEdgeDecoderSchedulerAlarmInternalInputNotConnectedOffId OBJECT-TYPE
    SYNTAX DisplayString
    MAX-ACCESS read-only
    STATUS current
    DESCRIPTION "."
    ::= { titanEdgeDecoderSchedulerAlarmInternalInputNotConnectedOffMonitors 2 }

titanEdgeDecoderSchedulerAlarmInternalInputNotConnectedOffIndex OBJECT-TYPE
    SYNTAX DisplayString
    MAX-ACCESS read-only
    STATUS current
    DESCRIPTION "."
    ::= { titanEdgeDecoderSchedulerAlarmInternalInputNotConnectedOffMonitors 2 }

titanEdgeDecoderSchedulerAlarmSystemRivermaxLicenseIssueOnNotification NOTIFICATION-TYPE
    OBJECTS {
        titanEdgeDecoderSchedulerAlarmSystemRivermaxLicenseIssueOnId,
        titanEdgeDecoderSchedulerAlarmSystemRivermaxLicenseIssueOnIndex
    }
    STATUS current
    DESCRIPTION "Hardware Mellanox Rivermax license issue"
    ::= { titanEdgeDecoderSchedulerAlarmSystemRivermaxLicenseIssueOn 1 }

titanEdgeDecoderSchedulerAlarmSystemRivermaxLicenseIssueOnId OBJECT-TYPE
    SYNTAX DisplayString
    MAX-ACCESS read-only
    STATUS current
    DESCRIPTION "."
    ::= { titanEdgeDecoderSchedulerAlarmSystemRivermaxLicenseIssueOn 1 2 }

titanEdgeDecoderSchedulerAlarmSystemRivermaxLicenseIssueOnIndex OBJECT-TYPE
    SYNTAX DisplayString
    MAX-ACCESS read-only
    STATUS current
    DESCRIPTION "."
    ::= { titanEdgeDecoderSchedulerAlarmSystemRivermaxLicenseIssueOn 1 2 }

titanEdgeDecoderSchedulerAlarmSystemRivermaxLicenseIssueOffNotification NOTIFICATION-TYPE
    OBJECTS {
        titanEdgeDecoderSchedulerAlarmSystemRivermaxLicenseIssueOffId,
        titanEdgeDecoderSchedulerAlarmSystemRivermaxLicenseIssueOffIndex
    }
    STATUS current
    DESCRIPTION "Hardware Mellanox Rivermax license issue"
    ::= { titanEdgeDecoderSchedulerAlarmSystemRivermaxLicenseIssueOn 2 }

titanEdgeDecoderSchedulerAlarmSystemRivermaxLicenseIssueOffId OBJECT-TYPE
    SYNTAX DisplayString
    MAX-ACCESS read-only
    STATUS current
    DESCRIPTION "."
    ::= { titanEdgeDecoderSchedulerAlarmSystemRivermaxLicenseIssueOffMonitors 2 }

titanEdgeDecoderSchedulerAlarmSystemRivermaxLicenseIssueOffIndex OBJECT-TYPE
    SYNTAX DisplayString
    MAX-ACCESS read-only
    STATUS current
    DESCRIPTION "."
    ::= { titanEdgeDecoderSchedulerAlarmSystemRivermaxLicenseIssueOffMonitors 2 }

titanEdgeDecoderSchedulerAlarmTsSmpte20227SignalMissingOnNotification NOTIFICATION-TYPE
    OBJECTS {
        titanEdgeDecoderSchedulerAlarmTsSmpte20227SignalMissingOnId,
        titanEdgeDecoderSchedulerAlarmTsSmpte20227SignalMissingOnIndex,
        titanEdgeDecoderSchedulerAlarmTsSmpte20227SignalMissingOnName
    }
    STATUS current
    DESCRIPTION "SMPTE 2022-7 signal is missing"
    ::= { titanEdgeDecoderSchedulerAlarmTsSmpte20227SignalMissingOn 1 }

titanEdgeDecoderSchedulerAlarmTsSmpte20227SignalMissingOnId OBJECT-TYPE
    SYNTAX DisplayString
    MAX-ACCESS read-only
    STATUS current
    DESCRIPTION "."
    ::= { titanEdgeDecoderSchedulerAlarmTsSmpte20227SignalMissingOn 1 2 }

titanEdgeDecoderSchedulerAlarmTsSmpte20227SignalMissingOnIndex OBJECT-TYPE
    SYNTAX DisplayString
    MAX-ACCESS read-only
    STATUS current
    DESCRIPTION "."
    ::= { titanEdgeDecoderSchedulerAlarmTsSmpte20227SignalMissingOn 1 2 }

titanEdgeDecoderSchedulerAlarmTsSmpte20227SignalMissingOnName OBJECT-TYPE
    SYNTAX DisplayString
    MAX-ACCESS read-only
    STATUS current
    DESCRIPTION "."
    ::= { titanEdgeDecoderSchedulerAlarmTsSmpte20227SignalMissingOn 1 2 }

titanEdgeDecoderSchedulerAlarmTsSmpte20227SignalMissingOffNotification NOTIFICATION-TYPE
    OBJECTS {
        titanEdgeDecoderSchedulerAlarmTsSmpte20227SignalMissingOffId,
        titanEdgeDecoderSchedulerAlarmTsSmpte20227SignalMissingOffIndex,
        titanEdgeDecoderSchedulerAlarmTsSmpte20227SignalMissingOffName
    }
    STATUS current
    DESCRIPTION "SMPTE 2022-7 signal is missing"
    ::= { titanEdgeDecoderSchedulerAlarmTsSmpte20227SignalMissingOn 2 }

titanEdgeDecoderSchedulerAlarmTsSmpte20227SignalMissingOffId OBJECT-TYPE
    SYNTAX DisplayString
    MAX-ACCESS read-only
    STATUS current
    DESCRIPTION "."
    ::= { titanEdgeDecoderSchedulerAlarmTsSmpte20227SignalMissingOffMonitors 2 }

titanEdgeDecoderSchedulerAlarmTsSmpte20227SignalMissingOffIndex OBJECT-TYPE
    SYNTAX DisplayString
    MAX-ACCESS read-only
    STATUS current
    DESCRIPTION "."
    ::= { titanEdgeDecoderSchedulerAlarmTsSmpte20227SignalMissingOffMonitors 2 }

titanEdgeDecoderSchedulerAlarmTsSmpte20227SignalMissingOffName OBJECT-TYPE
    SYNTAX DisplayString
    MAX-ACCESS read-only
    STATUS current
    DESCRIPTION "."
    ::= { titanEdgeDecoderSchedulerAlarmTsSmpte20227SignalMissingOffMonitors 2 }

titanEdgeDecoderSchedulerAlarmTsSmpte20227SkewTooLargeOnNotification NOTIFICATION-TYPE
    OBJECTS {
        titanEdgeDecoderSchedulerAlarmTsSmpte20227SkewTooLargeOnId,
        titanEdgeDecoderSchedulerAlarmTsSmpte20227SkewTooLargeOnIndex
    }
    STATUS current
    DESCRIPTION "SMPTE 2022-7 skew is too large"
    ::= { titanEdgeDecoderSchedulerAlarmTsSmpte20227SkewTooLargeOn 1 }

titanEdgeDecoderSchedulerAlarmTsSmpte20227SkewTooLargeOnId OBJECT-TYPE
    SYNTAX DisplayString
    MAX-ACCESS read-only
    STATUS current
    DESCRIPTION "."
    ::= { titanEdgeDecoderSchedulerAlarmTsSmpte20227SkewTooLargeOn 1 2 }

titanEdgeDecoderSchedulerAlarmTsSmpte20227SkewTooLargeOnIndex OBJECT-TYPE
    SYNTAX DisplayString
    MAX-ACCESS read-only
    STATUS current
    DESCRIPTION "."
    ::= { titanEdgeDecoderSchedulerAlarmTsSmpte20227SkewTooLargeOn 1 2 }

titanEdgeDecoderSchedulerAlarmTsSmpte20227SkewTooLargeOffNotification NOTIFICATION-TYPE
    OBJECTS {
        titanEdgeDecoderSchedulerAlarmTsSmpte20227SkewTooLargeOffId,
        titanEdgeDecoderSchedulerAlarmTsSmpte20227SkewTooLargeOffIndex
    }
    STATUS current
    DESCRIPTION "SMPTE 2022-7 skew is too large"
    ::= { titanEdgeDecoderSchedulerAlarmTsSmpte20227SkewTooLargeOn 2 }

titanEdgeDecoderSchedulerAlarmTsSmpte20227SkewTooLargeOffId OBJECT-TYPE
    SYNTAX DisplayString
    MAX-ACCESS read-only
    STATUS current
    DESCRIPTION "."
    ::= { titanEdgeDecoderSchedulerAlarmTsSmpte20227SkewTooLargeOffMonitors 2 }

titanEdgeDecoderSchedulerAlarmTsSmpte20227SkewTooLargeOffIndex OBJECT-TYPE
    SYNTAX DisplayString
    MAX-ACCESS read-only
    STATUS current
    DESCRIPTION "."
    ::= { titanEdgeDecoderSchedulerAlarmTsSmpte20227SkewTooLargeOffMonitors 2 }

titanEdgeDecoderSchedulerAlarmSystemEthernetUnknownOnNotification NOTIFICATION-TYPE
    OBJECTS {
        titanEdgeDecoderSchedulerAlarmSystemEthernetUnknownOnId,
        titanEdgeDecoderSchedulerAlarmSystemEthernetUnknownOnIndex,
        titanEdgeDecoderSchedulerAlarmSystemEthernetUnknownOnName
    }
    STATUS current
    DESCRIPTION "Ethernet link unknown"
    ::= { titanEdgeDecoderSchedulerAlarmSystemEthernetUnknownOn 1 }

titanEdgeDecoderSchedulerAlarmSystemEthernetUnknownOnId OBJECT-TYPE
    SYNTAX DisplayString
    MAX-ACCESS read-only
    STATUS current
    DESCRIPTION "."
    ::= { titanEdgeDecoderSchedulerAlarmSystemEthernetUnknownOn 1 2 }

titanEdgeDecoderSchedulerAlarmSystemEthernetUnknownOnIndex OBJECT-TYPE
    SYNTAX DisplayString
    MAX-ACCESS read-only
    STATUS current
    DESCRIPTION "."
    ::= { titanEdgeDecoderSchedulerAlarmSystemEthernetUnknownOn 1 2 }

titanEdgeDecoderSchedulerAlarmSystemEthernetUnknownOnName OBJECT-TYPE
    SYNTAX DisplayString
    MAX-ACCESS read-only
    STATUS current
    DESCRIPTION "."
    ::= { titanEdgeDecoderSchedulerAlarmSystemEthernetUnknownOn 1 2 }

titanEdgeDecoderSchedulerAlarmSystemEthernetUnknownOffNotification NOTIFICATION-TYPE
    OBJECTS {
        titanEdgeDecoderSchedulerAlarmSystemEthernetUnknownOffId,
        titanEdgeDecoderSchedulerAlarmSystemEthernetUnknownOffIndex,
        titanEdgeDecoderSchedulerAlarmSystemEthernetUnknownOffName
    }
    STATUS current
    DESCRIPTION "Ethernet link unknown"
    ::= { titanEdgeDecoderSchedulerAlarmSystemEthernetUnknownOn 2 }

titanEdgeDecoderSchedulerAlarmSystemEthernetUnknownOffId OBJECT-TYPE
    SYNTAX DisplayString
    MAX-ACCESS read-only
    STATUS current
    DESCRIPTION "."
    ::= { titanEdgeDecoderSchedulerAlarmSystemEthernetUnknownOffMonitors 2 }

titanEdgeDecoderSchedulerAlarmSystemEthernetUnknownOffIndex OBJECT-TYPE
    SYNTAX DisplayString
    MAX-ACCESS read-only
    STATUS current
    DESCRIPTION "."
    ::= { titanEdgeDecoderSchedulerAlarmSystemEthernetUnknownOffMonitors 2 }

titanEdgeDecoderSchedulerAlarmSystemEthernetUnknownOffName OBJECT-TYPE
    SYNTAX DisplayString
    MAX-ACCESS read-only
    STATUS current
    DESCRIPTION "."
    ::= { titanEdgeDecoderSchedulerAlarmSystemEthernetUnknownOffMonitors 2 }

titanEdgeDecoderSchedulerAlarmCompositionWatermarkingNotAvailableOnNotification NOTIFICATION-TYPE
    OBJECTS {
        titanEdgeDecoderSchedulerAlarmCompositionWatermarkingNotAvailableOnId,
        titanEdgeDecoderSchedulerAlarmCompositionWatermarkingNotAvailableOnName
    }
    STATUS current
    DESCRIPTION "Watermarking is not available"
    ::= { titanEdgeDecoderSchedulerAlarmCompositionWatermarkingNotAvailableOn 1 }

titanEdgeDecoderSchedulerAlarmCompositionWatermarkingNotAvailableOnId OBJECT-TYPE
    SYNTAX DisplayString
    MAX-ACCESS read-only
    STATUS current
    DESCRIPTION "."
    ::= { titanEdgeDecoderSchedulerAlarmCompositionWatermarkingNotAvailableOn 1 2 }

titanEdgeDecoderSchedulerAlarmCompositionWatermarkingNotAvailableOnName OBJECT-TYPE
    SYNTAX DisplayString
    MAX-ACCESS read-only
    STATUS current
    DESCRIPTION "."
    ::= { titanEdgeDecoderSchedulerAlarmCompositionWatermarkingNotAvailableOn 1 2 }

titanEdgeDecoderSchedulerAlarmCompositionWatermarkingNotAvailableOffNotification NOTIFICATION-TYPE
    OBJECTS {
        titanEdgeDecoderSchedulerAlarmCompositionWatermarkingNotAvailableOffId,
        titanEdgeDecoderSchedulerAlarmCompositionWatermarkingNotAvailableOffName
    }
    STATUS current
    DESCRIPTION "Watermarking is not available"
    ::= { titanEdgeDecoderSchedulerAlarmCompositionWatermarkingNotAvailableOn 2 }

titanEdgeDecoderSchedulerAlarmCompositionWatermarkingNotAvailableOffId OBJECT-TYPE
    SYNTAX DisplayString
    MAX-ACCESS read-only
    STATUS current
    DESCRIPTION "."
    ::= { titanEdgeDecoderSchedulerAlarmCompositionWatermarkingNotAvailableOffMonitors 2 }

titanEdgeDecoderSchedulerAlarmCompositionWatermarkingNotAvailableOffName OBJECT-TYPE
    SYNTAX DisplayString
    MAX-ACCESS read-only
    STATUS current
    DESCRIPTION "."
    ::= { titanEdgeDecoderSchedulerAlarmCompositionWatermarkingNotAvailableOffMonitors 2 }

titanEdgeDecoderSchedulerAlarmChannelLostOnNotification NOTIFICATION-TYPE
    OBJECTS {
        titanEdgeDecoderSchedulerAlarmChannelLostOnId
    }
    STATUS current
    DESCRIPTION "Channel is lost"
    ::= { titanEdgeDecoderSchedulerAlarmChannelLostOn 1 }

titanEdgeDecoderSchedulerAlarmChannelLostOnId OBJECT-TYPE
    SYNTAX DisplayString
    MAX-ACCESS read-only
    STATUS current
    DESCRIPTION "."
    ::= { titanEdgeDecoderSchedulerAlarmChannelLostOn 1 2 }

titanEdgeDecoderSchedulerAlarmChannelLostOffNotification NOTIFICATION-TYPE
    OBJECTS {
        titanEdgeDecoderSchedulerAlarmChannelLostOffId
    }
    STATUS current
    DESCRIPTION "Channel is lost"
    ::= { titanEdgeDecoderSchedulerAlarmChannelLostOn 2 }

titanEdgeDecoderSchedulerAlarmChannelLostOffId OBJECT-TYPE
    SYNTAX DisplayString
    MAX-ACCESS read-only
    STATUS current
    DESCRIPTION "."
    ::= { titanEdgeDecoderSchedulerAlarmChannelLostOffMonitors 2 }

titanEdgeDecoderSchedulerAlarm2110Smpte20227ConfigurationInvalidOnNotification NOTIFICATION-TYPE
    OBJECTS {
        titanEdgeDecoderSchedulerAlarm2110Smpte20227ConfigurationInvalidOnId,
        titanEdgeDecoderSchedulerAlarm2110Smpte20227ConfigurationInvalidOnIndex,
        titanEdgeDecoderSchedulerAlarm2110Smpte20227ConfigurationInvalidOnName
    }
    STATUS current
    DESCRIPTION "SMPTE 2022-7 configuration invalid for SMPTE 2110 output"
    ::= { titanEdgeDecoderSchedulerAlarm2110Smpte20227ConfigurationInvalidOn 1 }

titanEdgeDecoderSchedulerAlarm2110Smpte20227ConfigurationInvalidOnId OBJECT-TYPE
    SYNTAX DisplayString
    MAX-ACCESS read-only
    STATUS current
    DESCRIPTION "."
    ::= { titanEdgeDecoderSchedulerAlarm2110Smpte20227ConfigurationInvalidOn 1 2 }

titanEdgeDecoderSchedulerAlarm2110Smpte20227ConfigurationInvalidOnIndex OBJECT-TYPE
    SYNTAX DisplayString
    MAX-ACCESS read-only
    STATUS current
    DESCRIPTION "."
    ::= { titanEdgeDecoderSchedulerAlarm2110Smpte20227ConfigurationInvalidOn 1 2 }

titanEdgeDecoderSchedulerAlarm2110Smpte20227ConfigurationInvalidOnName OBJECT-TYPE
    SYNTAX DisplayString
    MAX-ACCESS read-only
    STATUS current
    DESCRIPTION "."
    ::= { titanEdgeDecoderSchedulerAlarm2110Smpte20227ConfigurationInvalidOn 1 2 }

titanEdgeDecoderSchedulerAlarm2110Smpte20227ConfigurationInvalidOffNotification NOTIFICATION-TYPE
    OBJECTS {
        titanEdgeDecoderSchedulerAlarm2110Smpte20227ConfigurationInvalidOffId,
        titanEdgeDecoderSchedulerAlarm2110Smpte20227ConfigurationInvalidOffIndex,
        titanEdgeDecoderSchedulerAlarm2110Smpte20227ConfigurationInvalidOffName
    }
    STATUS current
    DESCRIPTION "SMPTE 2022-7 configuration invalid for SMPTE 2110 output"
    ::= { titanEdgeDecoderSchedulerAlarm2110Smpte20227ConfigurationInvalidOn 2 }

titanEdgeDecoderSchedulerAlarm2110Smpte20227ConfigurationInvalidOffId OBJECT-TYPE
    SYNTAX DisplayString
    MAX-ACCESS read-only
    STATUS current
    DESCRIPTION "."
    ::= { titanEdgeDecoderSchedulerAlarm2110Smpte20227ConfigurationInvalidOffMonitors 2 }

titanEdgeDecoderSchedulerAlarm2110Smpte20227ConfigurationInvalidOffIndex OBJECT-TYPE
    SYNTAX DisplayString
    MAX-ACCESS read-only
    STATUS current
    DESCRIPTION "."
    ::= { titanEdgeDecoderSchedulerAlarm2110Smpte20227ConfigurationInvalidOffMonitors 2 }

titanEdgeDecoderSchedulerAlarm2110Smpte20227ConfigurationInvalidOffName OBJECT-TYPE
    SYNTAX DisplayString
    MAX-ACCESS read-only
    STATUS current
    DESCRIPTION "."
    ::= { titanEdgeDecoderSchedulerAlarm2110Smpte20227ConfigurationInvalidOffMonitors 2 }

titanEdgeDecoderSchedulerAlarmCompositionMCamLimitsReachedOnNotification NOTIFICATION-TYPE
    OBJECTS {
        titanEdgeDecoderSchedulerAlarmCompositionMCamLimitsReachedOnId,
        titanEdgeDecoderSchedulerAlarmCompositionMCamLimitsReachedOnIndex,
        titanEdgeDecoderSchedulerAlarmCompositionMCamLimitsReachedOnName
    }
    STATUS current
    DESCRIPTION "M-CAM capacity has reached the limit set"
    ::= { titanEdgeDecoderSchedulerAlarmCompositionMCamLimitsReachedOn 1 }

titanEdgeDecoderSchedulerAlarmCompositionMCamLimitsReachedOnId OBJECT-TYPE
    SYNTAX DisplayString
    MAX-ACCESS read-only
    STATUS current
    DESCRIPTION "."
    ::= { titanEdgeDecoderSchedulerAlarmCompositionMCamLimitsReachedOn 1 2 }

titanEdgeDecoderSchedulerAlarmCompositionMCamLimitsReachedOnIndex OBJECT-TYPE
    SYNTAX DisplayString
    MAX-ACCESS read-only
    STATUS current
    DESCRIPTION "."
    ::= { titanEdgeDecoderSchedulerAlarmCompositionMCamLimitsReachedOn 1 2 }

titanEdgeDecoderSchedulerAlarmCompositionMCamLimitsReachedOnName OBJECT-TYPE
    SYNTAX DisplayString
    MAX-ACCESS read-only
    STATUS current
    DESCRIPTION "."
    ::= { titanEdgeDecoderSchedulerAlarmCompositionMCamLimitsReachedOn 1 2 }

titanEdgeDecoderSchedulerAlarmCompositionMCamLimitsReachedOffNotification NOTIFICATION-TYPE
    OBJECTS {
        titanEdgeDecoderSchedulerAlarmCompositionMCamLimitsReachedOffId,
        titanEdgeDecoderSchedulerAlarmCompositionMCamLimitsReachedOffIndex,
        titanEdgeDecoderSchedulerAlarmCompositionMCamLimitsReachedOffName
    }
    STATUS current
    DESCRIPTION "M-CAM capacity has reached the limit set"
    ::= { titanEdgeDecoderSchedulerAlarmCompositionMCamLimitsReachedOn 2 }

titanEdgeDecoderSchedulerAlarmCompositionMCamLimitsReachedOffId OBJECT-TYPE
    SYNTAX DisplayString
    MAX-ACCESS read-only
    STATUS current
    DESCRIPTION "."
    ::= { titanEdgeDecoderSchedulerAlarmCompositionMCamLimitsReachedOffMonitors 2 }

titanEdgeDecoderSchedulerAlarmCompositionMCamLimitsReachedOffIndex OBJECT-TYPE
    SYNTAX DisplayString
    MAX-ACCESS read-only
    STATUS current
    DESCRIPTION "."
    ::= { titanEdgeDecoderSchedulerAlarmCompositionMCamLimitsReachedOffMonitors 2 }

titanEdgeDecoderSchedulerAlarmCompositionMCamLimitsReachedOffName OBJECT-TYPE
    SYNTAX DisplayString
    MAX-ACCESS read-only
    STATUS current
    DESCRIPTION "."
    ::= { titanEdgeDecoderSchedulerAlarmCompositionMCamLimitsReachedOffMonitors 2 }

titanEdgeDecoderSchedulerAlarmCompositionMCamHardwareErrorOnNotification NOTIFICATION-TYPE
    OBJECTS {
        titanEdgeDecoderSchedulerAlarmCompositionMCamHardwareErrorOnId,
        titanEdgeDecoderSchedulerAlarmCompositionMCamHardwareErrorOnIndex
    }
    STATUS current
    DESCRIPTION "M-CAM pin hardware capacity is full"
    ::= { titanEdgeDecoderSchedulerAlarmCompositionMCamHardwareErrorOn 1 }

titanEdgeDecoderSchedulerAlarmCompositionMCamHardwareErrorOnId OBJECT-TYPE
    SYNTAX DisplayString
    MAX-ACCESS read-only
    STATUS current
    DESCRIPTION "."
    ::= { titanEdgeDecoderSchedulerAlarmCompositionMCamHardwareErrorOn 1 2 }

titanEdgeDecoderSchedulerAlarmCompositionMCamHardwareErrorOnIndex OBJECT-TYPE
    SYNTAX DisplayString
    MAX-ACCESS read-only
    STATUS current
    DESCRIPTION "."
    ::= { titanEdgeDecoderSchedulerAlarmCompositionMCamHardwareErrorOn 1 2 }

titanEdgeDecoderSchedulerAlarmCompositionMCamHardwareErrorOffNotification NOTIFICATION-TYPE
    OBJECTS {
        titanEdgeDecoderSchedulerAlarmCompositionMCamHardwareErrorOffId,
        titanEdgeDecoderSchedulerAlarmCompositionMCamHardwareErrorOffIndex
    }
    STATUS current
    DESCRIPTION "M-CAM pin hardware capacity is full"
    ::= { titanEdgeDecoderSchedulerAlarmCompositionMCamHardwareErrorOn 2 }

titanEdgeDecoderSchedulerAlarmCompositionMCamHardwareErrorOffId OBJECT-TYPE
    SYNTAX DisplayString
    MAX-ACCESS read-only
    STATUS current
    DESCRIPTION "."
    ::= { titanEdgeDecoderSchedulerAlarmCompositionMCamHardwareErrorOffMonitors 2 }

titanEdgeDecoderSchedulerAlarmCompositionMCamHardwareErrorOffIndex OBJECT-TYPE
    SYNTAX DisplayString
    MAX-ACCESS read-only
    STATUS current
    DESCRIPTION "."
    ::= { titanEdgeDecoderSchedulerAlarmCompositionMCamHardwareErrorOffMonitors 2 }

titanEdgeDecoderSchedulerAlarmCompositionMCamDuplicatedProgramsOnNotification NOTIFICATION-TYPE
    OBJECTS {
        titanEdgeDecoderSchedulerAlarmCompositionMCamDuplicatedProgramsOnId,
        titanEdgeDecoderSchedulerAlarmCompositionMCamDuplicatedProgramsOnIndex,
        titanEdgeDecoderSchedulerAlarmCompositionMCamDuplicatedProgramsOnName
    }
    STATUS current
    DESCRIPTION "Duplicated programs detected on the M-CAM pin"
    ::= { titanEdgeDecoderSchedulerAlarmCompositionMCamDuplicatedProgramsOn 1 }

titanEdgeDecoderSchedulerAlarmCompositionMCamDuplicatedProgramsOnId OBJECT-TYPE
    SYNTAX DisplayString
    MAX-ACCESS read-only
    STATUS current
    DESCRIPTION "."
    ::= { titanEdgeDecoderSchedulerAlarmCompositionMCamDuplicatedProgramsOn 1 2 }

titanEdgeDecoderSchedulerAlarmCompositionMCamDuplicatedProgramsOnIndex OBJECT-TYPE
    SYNTAX DisplayString
    MAX-ACCESS read-only
    STATUS current
    DESCRIPTION "."
    ::= { titanEdgeDecoderSchedulerAlarmCompositionMCamDuplicatedProgramsOn 1 2 }

titanEdgeDecoderSchedulerAlarmCompositionMCamDuplicatedProgramsOnName OBJECT-TYPE
    SYNTAX DisplayString
    MAX-ACCESS read-only
    STATUS current
    DESCRIPTION "."
    ::= { titanEdgeDecoderSchedulerAlarmCompositionMCamDuplicatedProgramsOn 1 2 }

titanEdgeDecoderSchedulerAlarmCompositionMCamDuplicatedProgramsOffNotification NOTIFICATION-TYPE
    OBJECTS {
        titanEdgeDecoderSchedulerAlarmCompositionMCamDuplicatedProgramsOffId,
        titanEdgeDecoderSchedulerAlarmCompositionMCamDuplicatedProgramsOffIndex,
        titanEdgeDecoderSchedulerAlarmCompositionMCamDuplicatedProgramsOffName
    }
    STATUS current
    DESCRIPTION "Duplicated programs detected on the M-CAM pin"
    ::= { titanEdgeDecoderSchedulerAlarmCompositionMCamDuplicatedProgramsOn 2 }

titanEdgeDecoderSchedulerAlarmCompositionMCamDuplicatedProgramsOffId OBJECT-TYPE
    SYNTAX DisplayString
    MAX-ACCESS read-only
    STATUS current
    DESCRIPTION "."
    ::= { titanEdgeDecoderSchedulerAlarmCompositionMCamDuplicatedProgramsOffMonitors 2 }

titanEdgeDecoderSchedulerAlarmCompositionMCamDuplicatedProgramsOffIndex OBJECT-TYPE
    SYNTAX DisplayString
    MAX-ACCESS read-only
    STATUS current
    DESCRIPTION "."
    ::= { titanEdgeDecoderSchedulerAlarmCompositionMCamDuplicatedProgramsOffMonitors 2 }

titanEdgeDecoderSchedulerAlarmCompositionMCamDuplicatedProgramsOffName OBJECT-TYPE
    SYNTAX DisplayString
    MAX-ACCESS read-only
    STATUS current
    DESCRIPTION "."
    ::= { titanEdgeDecoderSchedulerAlarmCompositionMCamDuplicatedProgramsOffMonitors 2 }

titanEdgeDecoderProcessingLogProcessingFailureNotification NOTIFICATION-TYPE
    OBJECTS {
        titanEdgeDecoderProcessingLogProcessingFailureId
    }
    STATUS current
    DESCRIPTION "Processing failure"
    ::= { titanEdgeDecoderProcessingLogs 9 }

titanEdgeDecoderProcessingLogProcessingFailureId OBJECT-TYPE
    SYNTAX DisplayString
    MAX-ACCESS read-only
    STATUS current
    DESCRIPTION "."
    ::= { titanEdgeDecoderProcessingLogs 9 2 }

titanEdgeEncoderApiLogChannelAddedNotification NOTIFICATION-TYPE
    OBJECTS {
        titanEdgeEncoderApiLogChannelAddedId
    }
    STATUS current
    DESCRIPTION "Channel added"
    ::= { titanEdgeEncoderApiLogs 4 }

titanEdgeEncoderApiLogChannelAddedId OBJECT-TYPE
    SYNTAX DisplayString
    MAX-ACCESS read-only
    STATUS current
    DESCRIPTION "."
    ::= { titanEdgeEncoderApiLogs 4 2 }

titanEdgeEncoderApiLogChannelDeletedNotification NOTIFICATION-TYPE
    OBJECTS {
        titanEdgeEncoderApiLogChannelDeletedId
    }
    STATUS current
    DESCRIPTION "Channel deleted"
    ::= { titanEdgeEncoderApiLogs 5 }

titanEdgeEncoderApiLogChannelDeletedId OBJECT-TYPE
    SYNTAX DisplayString
    MAX-ACCESS read-only
    STATUS current
    DESCRIPTION "."
    ::= { titanEdgeEncoderApiLogs 5 2 }

titanEdgeEncoderApiLogChannelModifiedNotification NOTIFICATION-TYPE
    OBJECTS {
        titanEdgeEncoderApiLogChannelModifiedId
    }
    STATUS current
    DESCRIPTION "Channel modified"
    ::= { titanEdgeEncoderApiLogs 6 }

titanEdgeEncoderApiLogChannelModifiedId OBJECT-TYPE
    SYNTAX DisplayString
    MAX-ACCESS read-only
    STATUS current
    DESCRIPTION "."
    ::= { titanEdgeEncoderApiLogs 6 2 }

titanEdgeEncoderSchedulerLogChannelStartedNotification NOTIFICATION-TYPE
    OBJECTS {
        titanEdgeEncoderSchedulerLogChannelStartedId
    }
    STATUS current
    DESCRIPTION "Channel started"
    ::= { titanEdgeEncoderSchedulerLogs 7 }

titanEdgeEncoderSchedulerLogChannelStartedId OBJECT-TYPE
    SYNTAX DisplayString
    MAX-ACCESS read-only
    STATUS current
    DESCRIPTION "."
    ::= { titanEdgeEncoderSchedulerLogs 7 2 }

titanEdgeEncoderSchedulerLogChannelStoppedNotification NOTIFICATION-TYPE
    OBJECTS {
        titanEdgeEncoderSchedulerLogChannelStoppedId
    }
    STATUS current
    DESCRIPTION "Channel stopped"
    ::= { titanEdgeEncoderSchedulerLogs 8 }

titanEdgeEncoderSchedulerLogChannelStoppedId OBJECT-TYPE
    SYNTAX DisplayString
    MAX-ACCESS read-only
    STATUS current
    DESCRIPTION "."
    ::= { titanEdgeEncoderSchedulerLogs 8 2 }

titanEdgeEncoderSchedulerLogChannelFailoverInputChangedNotification NOTIFICATION-TYPE
    OBJECTS {
        titanEdgeEncoderSchedulerLogChannelFailoverInputChangedId,
        titanEdgeEncoderSchedulerLogChannelFailoverInputChangedIndex
    }
    STATUS current
    DESCRIPTION "Channel failover input changed"
    ::= { titanEdgeEncoderSchedulerLogs 10 }

titanEdgeEncoderSchedulerLogChannelFailoverInputChangedId OBJECT-TYPE
    SYNTAX DisplayString
    MAX-ACCESS read-only
    STATUS current
    DESCRIPTION "."
    ::= { titanEdgeEncoderSchedulerLogs 10 2 }

titanEdgeEncoderSchedulerLogChannelFailoverInputChangedIndex OBJECT-TYPE
    SYNTAX DisplayString
    MAX-ACCESS read-only
    STATUS current
    DESCRIPTION "."
    ::= { titanEdgeEncoderSchedulerLogs 10 2 }

titanEdgeEncoderSchedulerAlarmCompositionVideoSourceMissingOnNotification NOTIFICATION-TYPE
    OBJECTS {
        titanEdgeEncoderSchedulerAlarmCompositionVideoSourceMissingOnId
    }
    STATUS current
    DESCRIPTION "Video source missing"
    ::= { titanEdgeEncoderSchedulerAlarmCompositionVideoSourceMissingOn 1 }

titanEdgeEncoderSchedulerAlarmCompositionVideoSourceMissingOnId OBJECT-TYPE
    SYNTAX DisplayString
    MAX-ACCESS read-only
    STATUS current
    DESCRIPTION "."
    ::= { titanEdgeEncoderSchedulerAlarmCompositionVideoSourceMissingOn 1 2 }

titanEdgeEncoderSchedulerAlarmCompositionVideoSourceMissingOffNotification NOTIFICATION-TYPE
    OBJECTS {
        titanEdgeEncoderSchedulerAlarmCompositionVideoSourceMissingOffId
    }
    STATUS current
    DESCRIPTION "Video source missing"
    ::= { titanEdgeEncoderSchedulerAlarmCompositionVideoSourceMissingOn 2 }

titanEdgeEncoderSchedulerAlarmCompositionVideoSourceMissingOffId OBJECT-TYPE
    SYNTAX DisplayString
    MAX-ACCESS read-only
    STATUS current
    DESCRIPTION "."
    ::= { titanEdgeEncoderSchedulerAlarmCompositionVideoSourceMissingOffMonitors 2 }

titanEdgeEncoderSchedulerAlarmCompositionAudioSourceMissingOnNotification NOTIFICATION-TYPE
    OBJECTS {
        titanEdgeEncoderSchedulerAlarmCompositionAudioSourceMissingOnId,
        titanEdgeEncoderSchedulerAlarmCompositionAudioSourceMissingOnIndex
    }
    STATUS current
    DESCRIPTION "Audio source missing"
    ::= { titanEdgeEncoderSchedulerAlarmCompositionAudioSourceMissingOn 1 }

titanEdgeEncoderSchedulerAlarmCompositionAudioSourceMissingOnId OBJECT-TYPE
    SYNTAX DisplayString
    MAX-ACCESS read-only
    STATUS current
    DESCRIPTION "."
    ::= { titanEdgeEncoderSchedulerAlarmCompositionAudioSourceMissingOn 1 2 }

titanEdgeEncoderSchedulerAlarmCompositionAudioSourceMissingOnIndex OBJECT-TYPE
    SYNTAX DisplayString
    MAX-ACCESS read-only
    STATUS current
    DESCRIPTION "."
    ::= { titanEdgeEncoderSchedulerAlarmCompositionAudioSourceMissingOn 1 2 }

titanEdgeEncoderSchedulerAlarmCompositionAudioSourceMissingOffNotification NOTIFICATION-TYPE
    OBJECTS {
        titanEdgeEncoderSchedulerAlarmCompositionAudioSourceMissingOffId,
        titanEdgeEncoderSchedulerAlarmCompositionAudioSourceMissingOffIndex
    }
    STATUS current
    DESCRIPTION "Audio source missing"
    ::= { titanEdgeEncoderSchedulerAlarmCompositionAudioSourceMissingOn 2 }

titanEdgeEncoderSchedulerAlarmCompositionAudioSourceMissingOffId OBJECT-TYPE
    SYNTAX DisplayString
    MAX-ACCESS read-only
    STATUS current
    DESCRIPTION "."
    ::= { titanEdgeEncoderSchedulerAlarmCompositionAudioSourceMissingOffMonitors 2 }

titanEdgeEncoderSchedulerAlarmCompositionAudioSourceMissingOffIndex OBJECT-TYPE
    SYNTAX DisplayString
    MAX-ACCESS read-only
    STATUS current
    DESCRIPTION "."
    ::= { titanEdgeEncoderSchedulerAlarmCompositionAudioSourceMissingOffMonitors 2 }

titanEdgeEncoderSchedulerAlarmLicenseMissingOnNotification NOTIFICATION-TYPE
    OBJECTS {
        titanEdgeEncoderSchedulerAlarmLicenseMissingOnId,
        titanEdgeEncoderSchedulerAlarmLicenseMissingOnName
    }
    STATUS current
    DESCRIPTION "License Missing"
    ::= { titanEdgeEncoderSchedulerAlarmLicenseMissingOn 1 }

titanEdgeEncoderSchedulerAlarmLicenseMissingOnId OBJECT-TYPE
    SYNTAX DisplayString
    MAX-ACCESS read-only
    STATUS current
    DESCRIPTION "."
    ::= { titanEdgeEncoderSchedulerAlarmLicenseMissingOn 1 2 }

titanEdgeEncoderSchedulerAlarmLicenseMissingOnName OBJECT-TYPE
    SYNTAX DisplayString
    MAX-ACCESS read-only
    STATUS current
    DESCRIPTION "."
    ::= { titanEdgeEncoderSchedulerAlarmLicenseMissingOn 1 2 }

titanEdgeEncoderSchedulerAlarmLicenseMissingOffNotification NOTIFICATION-TYPE
    OBJECTS {
        titanEdgeEncoderSchedulerAlarmLicenseMissingOffId,
        titanEdgeEncoderSchedulerAlarmLicenseMissingOffName
    }
    STATUS current
    DESCRIPTION "License Missing"
    ::= { titanEdgeEncoderSchedulerAlarmLicenseMissingOn 2 }

titanEdgeEncoderSchedulerAlarmLicenseMissingOffId OBJECT-TYPE
    SYNTAX DisplayString
    MAX-ACCESS read-only
    STATUS current
    DESCRIPTION "."
    ::= { titanEdgeEncoderSchedulerAlarmLicenseMissingOffMonitors 2 }

titanEdgeEncoderSchedulerAlarmLicenseMissingOffName OBJECT-TYPE
    SYNTAX DisplayString
    MAX-ACCESS read-only
    STATUS current
    DESCRIPTION "."
    ::= { titanEdgeEncoderSchedulerAlarmLicenseMissingOffMonitors 2 }

titanEdgeEncoderSchedulerAlarmCompositionVideoSourceIncompatibleOnNotification NOTIFICATION-TYPE
    OBJECTS {
        titanEdgeEncoderSchedulerAlarmCompositionVideoSourceIncompatibleOnId
    }
    STATUS current
    DESCRIPTION "Video source incompatible"
    ::= { titanEdgeEncoderSchedulerAlarmCompositionVideoSourceIncompatibleOn 1 }

titanEdgeEncoderSchedulerAlarmCompositionVideoSourceIncompatibleOnId OBJECT-TYPE
    SYNTAX DisplayString
    MAX-ACCESS read-only
    STATUS current
    DESCRIPTION "."
    ::= { titanEdgeEncoderSchedulerAlarmCompositionVideoSourceIncompatibleOn 1 2 }

titanEdgeEncoderSchedulerAlarmCompositionVideoSourceIncompatibleOffNotification NOTIFICATION-TYPE
    OBJECTS {
        titanEdgeEncoderSchedulerAlarmCompositionVideoSourceIncompatibleOffId
    }
    STATUS current
    DESCRIPTION "Video source incompatible"
    ::= { titanEdgeEncoderSchedulerAlarmCompositionVideoSourceIncompatibleOn 2 }

titanEdgeEncoderSchedulerAlarmCompositionVideoSourceIncompatibleOffId OBJECT-TYPE
    SYNTAX DisplayString
    MAX-ACCESS read-only
    STATUS current
    DESCRIPTION "."
    ::= { titanEdgeEncoderSchedulerAlarmCompositionVideoSourceIncompatibleOffMonitors 2 }

titanEdgeEncoderSchedulerAlarmCompositionVideoSourceNotSupportedOnNotification NOTIFICATION-TYPE
    OBJECTS {
        titanEdgeEncoderSchedulerAlarmCompositionVideoSourceNotSupportedOnId
    }
    STATUS current
    DESCRIPTION "Video source not supported"
    ::= { titanEdgeEncoderSchedulerAlarmCompositionVideoSourceNotSupportedOn 1 }

titanEdgeEncoderSchedulerAlarmCompositionVideoSourceNotSupportedOnId OBJECT-TYPE
    SYNTAX DisplayString
    MAX-ACCESS read-only
    STATUS current
    DESCRIPTION "."
    ::= { titanEdgeEncoderSchedulerAlarmCompositionVideoSourceNotSupportedOn 1 2 }

titanEdgeEncoderSchedulerAlarmCompositionVideoSourceNotSupportedOffNotification NOTIFICATION-TYPE
    OBJECTS {
        titanEdgeEncoderSchedulerAlarmCompositionVideoSourceNotSupportedOffId
    }
    STATUS current
    DESCRIPTION "Video source not supported"
    ::= { titanEdgeEncoderSchedulerAlarmCompositionVideoSourceNotSupportedOn 2 }

titanEdgeEncoderSchedulerAlarmCompositionVideoSourceNotSupportedOffId OBJECT-TYPE
    SYNTAX DisplayString
    MAX-ACCESS read-only
    STATUS current
    DESCRIPTION "."
    ::= { titanEdgeEncoderSchedulerAlarmCompositionVideoSourceNotSupportedOffMonitors 2 }

titanEdgeEncoderSchedulerAlarmCompositionAudioSourceIncompatibleOnNotification NOTIFICATION-TYPE
    OBJECTS {
        titanEdgeEncoderSchedulerAlarmCompositionAudioSourceIncompatibleOnId,
        titanEdgeEncoderSchedulerAlarmCompositionAudioSourceIncompatibleOnIndex
    }
    STATUS current
    DESCRIPTION "Audio source incompatible"
    ::= { titanEdgeEncoderSchedulerAlarmCompositionAudioSourceIncompatibleOn 1 }

titanEdgeEncoderSchedulerAlarmCompositionAudioSourceIncompatibleOnId OBJECT-TYPE
    SYNTAX DisplayString
    MAX-ACCESS read-only
    STATUS current
    DESCRIPTION "."
    ::= { titanEdgeEncoderSchedulerAlarmCompositionAudioSourceIncompatibleOn 1 2 }

titanEdgeEncoderSchedulerAlarmCompositionAudioSourceIncompatibleOnIndex OBJECT-TYPE
    SYNTAX DisplayString
    MAX-ACCESS read-only
    STATUS current
    DESCRIPTION "."
    ::= { titanEdgeEncoderSchedulerAlarmCompositionAudioSourceIncompatibleOn 1 2 }

titanEdgeEncoderSchedulerAlarmCompositionAudioSourceIncompatibleOffNotification NOTIFICATION-TYPE
    OBJECTS {
        titanEdgeEncoderSchedulerAlarmCompositionAudioSourceIncompatibleOffId,
        titanEdgeEncoderSchedulerAlarmCompositionAudioSourceIncompatibleOffIndex
    }
    STATUS current
    DESCRIPTION "Audio source incompatible"
    ::= { titanEdgeEncoderSchedulerAlarmCompositionAudioSourceIncompatibleOn 2 }

titanEdgeEncoderSchedulerAlarmCompositionAudioSourceIncompatibleOffId OBJECT-TYPE
    SYNTAX DisplayString
    MAX-ACCESS read-only
    STATUS current
    DESCRIPTION "."
    ::= { titanEdgeEncoderSchedulerAlarmCompositionAudioSourceIncompatibleOffMonitors 2 }

titanEdgeEncoderSchedulerAlarmCompositionAudioSourceIncompatibleOffIndex OBJECT-TYPE
    SYNTAX DisplayString
    MAX-ACCESS read-only
    STATUS current
    DESCRIPTION "."
    ::= { titanEdgeEncoderSchedulerAlarmCompositionAudioSourceIncompatibleOffMonitors 2 }

titanEdgeEncoderSchedulerAlarmCompositionAudioSourceInactiveOnNotification NOTIFICATION-TYPE
    OBJECTS {
        titanEdgeEncoderSchedulerAlarmCompositionAudioSourceInactiveOnId,
        titanEdgeEncoderSchedulerAlarmCompositionAudioSourceInactiveOnIndex
    }
    STATUS current
    DESCRIPTION "Audio source inactive"
    ::= { titanEdgeEncoderSchedulerAlarmCompositionAudioSourceInactiveOn 1 }

titanEdgeEncoderSchedulerAlarmCompositionAudioSourceInactiveOnId OBJECT-TYPE
    SYNTAX DisplayString
    MAX-ACCESS read-only
    STATUS current
    DESCRIPTION "."
    ::= { titanEdgeEncoderSchedulerAlarmCompositionAudioSourceInactiveOn 1 2 }

titanEdgeEncoderSchedulerAlarmCompositionAudioSourceInactiveOnIndex OBJECT-TYPE
    SYNTAX DisplayString
    MAX-ACCESS read-only
    STATUS current
    DESCRIPTION "."
    ::= { titanEdgeEncoderSchedulerAlarmCompositionAudioSourceInactiveOn 1 2 }

titanEdgeEncoderSchedulerAlarmCompositionAudioSourceInactiveOffNotification NOTIFICATION-TYPE
    OBJECTS {
        titanEdgeEncoderSchedulerAlarmCompositionAudioSourceInactiveOffId,
        titanEdgeEncoderSchedulerAlarmCompositionAudioSourceInactiveOffIndex
    }
    STATUS current
    DESCRIPTION "Audio source inactive"
    ::= { titanEdgeEncoderSchedulerAlarmCompositionAudioSourceInactiveOn 2 }

titanEdgeEncoderSchedulerAlarmCompositionAudioSourceInactiveOffId OBJECT-TYPE
    SYNTAX DisplayString
    MAX-ACCESS read-only
    STATUS current
    DESCRIPTION "."
    ::= { titanEdgeEncoderSchedulerAlarmCompositionAudioSourceInactiveOffMonitors 2 }

titanEdgeEncoderSchedulerAlarmCompositionAudioSourceInactiveOffIndex OBJECT-TYPE
    SYNTAX DisplayString
    MAX-ACCESS read-only
    STATUS current
    DESCRIPTION "."
    ::= { titanEdgeEncoderSchedulerAlarmCompositionAudioSourceInactiveOffMonitors 2 }

titanEdgeEncoderSchedulerAlarmTsOutputBitrateDifferentOnNotification NOTIFICATION-TYPE
    OBJECTS {
        titanEdgeEncoderSchedulerAlarmTsOutputBitrateDifferentOnId
    }
    STATUS current
    DESCRIPTION "Program output bitrate is different than configured"
    ::= { titanEdgeEncoderSchedulerAlarmTsOutputBitrateDifferentOn 1 }

titanEdgeEncoderSchedulerAlarmTsOutputBitrateDifferentOnId OBJECT-TYPE
    SYNTAX DisplayString
    MAX-ACCESS read-only
    STATUS current
    DESCRIPTION "."
    ::= { titanEdgeEncoderSchedulerAlarmTsOutputBitrateDifferentOn 1 2 }

titanEdgeEncoderSchedulerAlarmTsOutputBitrateDifferentOffNotification NOTIFICATION-TYPE
    OBJECTS {
        titanEdgeEncoderSchedulerAlarmTsOutputBitrateDifferentOffId
    }
    STATUS current
    DESCRIPTION "Program output bitrate is different than configured"
    ::= { titanEdgeEncoderSchedulerAlarmTsOutputBitrateDifferentOn 2 }

titanEdgeEncoderSchedulerAlarmTsOutputBitrateDifferentOffId OBJECT-TYPE
    SYNTAX DisplayString
    MAX-ACCESS read-only
    STATUS current
    DESCRIPTION "."
    ::= { titanEdgeEncoderSchedulerAlarmTsOutputBitrateDifferentOffMonitors 2 }

titanEdgeEncoderSchedulerAlarmChannelInternalErrorOnNotification NOTIFICATION-TYPE
    OBJECTS {
        titanEdgeEncoderSchedulerAlarmChannelInternalErrorOnId
    }
    STATUS current
    DESCRIPTION "Channel internal error"
    ::= { titanEdgeEncoderSchedulerAlarmChannelInternalErrorOn 1 }

titanEdgeEncoderSchedulerAlarmChannelInternalErrorOnId OBJECT-TYPE
    SYNTAX DisplayString
    MAX-ACCESS read-only
    STATUS current
    DESCRIPTION "."
    ::= { titanEdgeEncoderSchedulerAlarmChannelInternalErrorOn 1 2 }

titanEdgeEncoderSchedulerAlarmChannelInternalErrorOffNotification NOTIFICATION-TYPE
    OBJECTS {
        titanEdgeEncoderSchedulerAlarmChannelInternalErrorOffId
    }
    STATUS current
    DESCRIPTION "Channel internal error"
    ::= { titanEdgeEncoderSchedulerAlarmChannelInternalErrorOn 2 }

titanEdgeEncoderSchedulerAlarmChannelInternalErrorOffId OBJECT-TYPE
    SYNTAX DisplayString
    MAX-ACCESS read-only
    STATUS current
    DESCRIPTION "."
    ::= { titanEdgeEncoderSchedulerAlarmChannelInternalErrorOffMonitors 2 }

titanEdgeEncoderSchedulerAlarmSystemExtensionPinUnknownOnNotification NOTIFICATION-TYPE
    OBJECTS {
        titanEdgeEncoderSchedulerAlarmSystemExtensionPinUnknownOnId,
        titanEdgeEncoderSchedulerAlarmSystemExtensionPinUnknownOnIndex
    }
    STATUS current
    DESCRIPTION "Hardware extension pin unknown"
    ::= { titanEdgeEncoderSchedulerAlarmSystemExtensionPinUnknownOn 1 }

titanEdgeEncoderSchedulerAlarmSystemExtensionPinUnknownOnId OBJECT-TYPE
    SYNTAX DisplayString
    MAX-ACCESS read-only
    STATUS current
    DESCRIPTION "."
    ::= { titanEdgeEncoderSchedulerAlarmSystemExtensionPinUnknownOn 1 2 }

titanEdgeEncoderSchedulerAlarmSystemExtensionPinUnknownOnIndex OBJECT-TYPE
    SYNTAX DisplayString
    MAX-ACCESS read-only
    STATUS current
    DESCRIPTION "."
    ::= { titanEdgeEncoderSchedulerAlarmSystemExtensionPinUnknownOn 1 2 }

titanEdgeEncoderSchedulerAlarmSystemExtensionPinUnknownOffNotification NOTIFICATION-TYPE
    OBJECTS {
        titanEdgeEncoderSchedulerAlarmSystemExtensionPinUnknownOffId,
        titanEdgeEncoderSchedulerAlarmSystemExtensionPinUnknownOffIndex
    }
    STATUS current
    DESCRIPTION "Hardware extension pin unknown"
    ::= { titanEdgeEncoderSchedulerAlarmSystemExtensionPinUnknownOn 2 }

titanEdgeEncoderSchedulerAlarmSystemExtensionPinUnknownOffId OBJECT-TYPE
    SYNTAX DisplayString
    MAX-ACCESS read-only
    STATUS current
    DESCRIPTION "."
    ::= { titanEdgeEncoderSchedulerAlarmSystemExtensionPinUnknownOffMonitors 2 }

titanEdgeEncoderSchedulerAlarmSystemExtensionPinUnknownOffIndex OBJECT-TYPE
    SYNTAX DisplayString
    MAX-ACCESS read-only
    STATUS current
    DESCRIPTION "."
    ::= { titanEdgeEncoderSchedulerAlarmSystemExtensionPinUnknownOffMonitors 2 }

titanEdgeEncoderSchedulerAlarmSystemExtensionPinInConflictOnNotification NOTIFICATION-TYPE
    OBJECTS {
        titanEdgeEncoderSchedulerAlarmSystemExtensionPinInConflictOnId,
        titanEdgeEncoderSchedulerAlarmSystemExtensionPinInConflictOnIndex
    }
    STATUS current
    DESCRIPTION "Hardware extension pin in conflict"
    ::= { titanEdgeEncoderSchedulerAlarmSystemExtensionPinInConflictOn 1 }

titanEdgeEncoderSchedulerAlarmSystemExtensionPinInConflictOnId OBJECT-TYPE
    SYNTAX DisplayString
    MAX-ACCESS read-only
    STATUS current
    DESCRIPTION "."
    ::= { titanEdgeEncoderSchedulerAlarmSystemExtensionPinInConflictOn 1 2 }

titanEdgeEncoderSchedulerAlarmSystemExtensionPinInConflictOnIndex OBJECT-TYPE
    SYNTAX DisplayString
    MAX-ACCESS read-only
    STATUS current
    DESCRIPTION "."
    ::= { titanEdgeEncoderSchedulerAlarmSystemExtensionPinInConflictOn 1 2 }

titanEdgeEncoderSchedulerAlarmSystemExtensionPinInConflictOffNotification NOTIFICATION-TYPE
    OBJECTS {
        titanEdgeEncoderSchedulerAlarmSystemExtensionPinInConflictOffId,
        titanEdgeEncoderSchedulerAlarmSystemExtensionPinInConflictOffIndex
    }
    STATUS current
    DESCRIPTION "Hardware extension pin in conflict"
    ::= { titanEdgeEncoderSchedulerAlarmSystemExtensionPinInConflictOn 2 }

titanEdgeEncoderSchedulerAlarmSystemExtensionPinInConflictOffId OBJECT-TYPE
    SYNTAX DisplayString
    MAX-ACCESS read-only
    STATUS current
    DESCRIPTION "."
    ::= { titanEdgeEncoderSchedulerAlarmSystemExtensionPinInConflictOffMonitors 2 }

titanEdgeEncoderSchedulerAlarmSystemExtensionPinInConflictOffIndex OBJECT-TYPE
    SYNTAX DisplayString
    MAX-ACCESS read-only
    STATUS current
    DESCRIPTION "."
    ::= { titanEdgeEncoderSchedulerAlarmSystemExtensionPinInConflictOffMonitors 2 }

titanEdgeEncoderSchedulerAlarmSystemExtensionPinConfigurationInvalidOnNotification NOTIFICATION-TYPE
    OBJECTS {
        titanEdgeEncoderSchedulerAlarmSystemExtensionPinConfigurationInvalidOnId,
        titanEdgeEncoderSchedulerAlarmSystemExtensionPinConfigurationInvalidOnIndex
    }
    STATUS current
    DESCRIPTION "Hardware extension pin configuration invalid"
    ::= { titanEdgeEncoderSchedulerAlarmSystemExtensionPinConfigurationInvalidOn 1 }

titanEdgeEncoderSchedulerAlarmSystemExtensionPinConfigurationInvalidOnId OBJECT-TYPE
    SYNTAX DisplayString
    MAX-ACCESS read-only
    STATUS current
    DESCRIPTION "."
    ::= { titanEdgeEncoderSchedulerAlarmSystemExtensionPinConfigurationInvalidOn 1 2 }

titanEdgeEncoderSchedulerAlarmSystemExtensionPinConfigurationInvalidOnIndex OBJECT-TYPE
    SYNTAX DisplayString
    MAX-ACCESS read-only
    STATUS current
    DESCRIPTION "."
    ::= { titanEdgeEncoderSchedulerAlarmSystemExtensionPinConfigurationInvalidOn 1 2 }

titanEdgeEncoderSchedulerAlarmSystemExtensionPinConfigurationInvalidOffNotification NOTIFICATION-TYPE
    OBJECTS {
        titanEdgeEncoderSchedulerAlarmSystemExtensionPinConfigurationInvalidOffId,
        titanEdgeEncoderSchedulerAlarmSystemExtensionPinConfigurationInvalidOffIndex
    }
    STATUS current
    DESCRIPTION "Hardware extension pin configuration invalid"
    ::= { titanEdgeEncoderSchedulerAlarmSystemExtensionPinConfigurationInvalidOn 2 }

titanEdgeEncoderSchedulerAlarmSystemExtensionPinConfigurationInvalidOffId OBJECT-TYPE
    SYNTAX DisplayString
    MAX-ACCESS read-only
    STATUS current
    DESCRIPTION "."
    ::= { titanEdgeEncoderSchedulerAlarmSystemExtensionPinConfigurationInvalidOffMonitors 2 }

titanEdgeEncoderSchedulerAlarmSystemExtensionPinConfigurationInvalidOffIndex OBJECT-TYPE
    SYNTAX DisplayString
    MAX-ACCESS read-only
    STATUS current
    DESCRIPTION "."
    ::= { titanEdgeEncoderSchedulerAlarmSystemExtensionPinConfigurationInvalidOffMonitors 2 }

titanEdgeEncoderSchedulerAlarmSystemRivermaxLicenseIssueOnNotification NOTIFICATION-TYPE
    OBJECTS {
        titanEdgeEncoderSchedulerAlarmSystemRivermaxLicenseIssueOnId,
        titanEdgeEncoderSchedulerAlarmSystemRivermaxLicenseIssueOnIndex
    }
    STATUS current
    DESCRIPTION "Hardware Mellanox Rivermax license issue"
    ::= { titanEdgeEncoderSchedulerAlarmSystemRivermaxLicenseIssueOn 1 }

titanEdgeEncoderSchedulerAlarmSystemRivermaxLicenseIssueOnId OBJECT-TYPE
    SYNTAX DisplayString
    MAX-ACCESS read-only
    STATUS current
    DESCRIPTION "."
    ::= { titanEdgeEncoderSchedulerAlarmSystemRivermaxLicenseIssueOn 1 2 }

titanEdgeEncoderSchedulerAlarmSystemRivermaxLicenseIssueOnIndex OBJECT-TYPE
    SYNTAX DisplayString
    MAX-ACCESS read-only
    STATUS current
    DESCRIPTION "."
    ::= { titanEdgeEncoderSchedulerAlarmSystemRivermaxLicenseIssueOn 1 2 }

titanEdgeEncoderSchedulerAlarmSystemRivermaxLicenseIssueOffNotification NOTIFICATION-TYPE
    OBJECTS {
        titanEdgeEncoderSchedulerAlarmSystemRivermaxLicenseIssueOffId,
        titanEdgeEncoderSchedulerAlarmSystemRivermaxLicenseIssueOffIndex
    }
    STATUS current
    DESCRIPTION "Hardware Mellanox Rivermax license issue"
    ::= { titanEdgeEncoderSchedulerAlarmSystemRivermaxLicenseIssueOn 2 }

titanEdgeEncoderSchedulerAlarmSystemRivermaxLicenseIssueOffId OBJECT-TYPE
    SYNTAX DisplayString
    MAX-ACCESS read-only
    STATUS current
    DESCRIPTION "."
    ::= { titanEdgeEncoderSchedulerAlarmSystemRivermaxLicenseIssueOffMonitors 2 }

titanEdgeEncoderSchedulerAlarmSystemRivermaxLicenseIssueOffIndex OBJECT-TYPE
    SYNTAX DisplayString
    MAX-ACCESS read-only
    STATUS current
    DESCRIPTION "."
    ::= { titanEdgeEncoderSchedulerAlarmSystemRivermaxLicenseIssueOffMonitors 2 }

titanEdgeEncoderSchedulerAlarmTsOccupancyBitrateInvalidOnNotification NOTIFICATION-TYPE
    OBJECTS {
        titanEdgeEncoderSchedulerAlarmTsOccupancyBitrateInvalidOnId
    }
    STATUS current
    DESCRIPTION "Program occupancy bitrate is different than configured"
    ::= { titanEdgeEncoderSchedulerAlarmTsOccupancyBitrateInvalidOn 1 }

titanEdgeEncoderSchedulerAlarmTsOccupancyBitrateInvalidOnId OBJECT-TYPE
    SYNTAX DisplayString
    MAX-ACCESS read-only
    STATUS current
    DESCRIPTION "."
    ::= { titanEdgeEncoderSchedulerAlarmTsOccupancyBitrateInvalidOn 1 2 }

titanEdgeEncoderSchedulerAlarmTsOccupancyBitrateInvalidOffNotification NOTIFICATION-TYPE
    OBJECTS {
        titanEdgeEncoderSchedulerAlarmTsOccupancyBitrateInvalidOffId
    }
    STATUS current
    DESCRIPTION "Program occupancy bitrate is different than configured"
    ::= { titanEdgeEncoderSchedulerAlarmTsOccupancyBitrateInvalidOn 2 }

titanEdgeEncoderSchedulerAlarmTsOccupancyBitrateInvalidOffId OBJECT-TYPE
    SYNTAX DisplayString
    MAX-ACCESS read-only
    STATUS current
    DESCRIPTION "."
    ::= { titanEdgeEncoderSchedulerAlarmTsOccupancyBitrateInvalidOffMonitors 2 }

titanEdgeEncoderSchedulerAlarmSystemEthernetUnknownOnNotification NOTIFICATION-TYPE
    OBJECTS {
        titanEdgeEncoderSchedulerAlarmSystemEthernetUnknownOnId,
        titanEdgeEncoderSchedulerAlarmSystemEthernetUnknownOnIndex,
        titanEdgeEncoderSchedulerAlarmSystemEthernetUnknownOnName
    }
    STATUS current
    DESCRIPTION "Ethernet link unknown"
    ::= { titanEdgeEncoderSchedulerAlarmSystemEthernetUnknownOn 1 }

titanEdgeEncoderSchedulerAlarmSystemEthernetUnknownOnId OBJECT-TYPE
    SYNTAX DisplayString
    MAX-ACCESS read-only
    STATUS current
    DESCRIPTION "."
    ::= { titanEdgeEncoderSchedulerAlarmSystemEthernetUnknownOn 1 2 }

titanEdgeEncoderSchedulerAlarmSystemEthernetUnknownOnIndex OBJECT-TYPE
    SYNTAX DisplayString
    MAX-ACCESS read-only
    STATUS current
    DESCRIPTION "."
    ::= { titanEdgeEncoderSchedulerAlarmSystemEthernetUnknownOn 1 2 }

titanEdgeEncoderSchedulerAlarmSystemEthernetUnknownOnName OBJECT-TYPE
    SYNTAX DisplayString
    MAX-ACCESS read-only
    STATUS current
    DESCRIPTION "."
    ::= { titanEdgeEncoderSchedulerAlarmSystemEthernetUnknownOn 1 2 }

titanEdgeEncoderSchedulerAlarmSystemEthernetUnknownOffNotification NOTIFICATION-TYPE
    OBJECTS {
        titanEdgeEncoderSchedulerAlarmSystemEthernetUnknownOffId,
        titanEdgeEncoderSchedulerAlarmSystemEthernetUnknownOffIndex,
        titanEdgeEncoderSchedulerAlarmSystemEthernetUnknownOffName
    }
    STATUS current
    DESCRIPTION "Ethernet link unknown"
    ::= { titanEdgeEncoderSchedulerAlarmSystemEthernetUnknownOn 2 }

titanEdgeEncoderSchedulerAlarmSystemEthernetUnknownOffId OBJECT-TYPE
    SYNTAX DisplayString
    MAX-ACCESS read-only
    STATUS current
    DESCRIPTION "."
    ::= { titanEdgeEncoderSchedulerAlarmSystemEthernetUnknownOffMonitors 2 }

titanEdgeEncoderSchedulerAlarmSystemEthernetUnknownOffIndex OBJECT-TYPE
    SYNTAX DisplayString
    MAX-ACCESS read-only
    STATUS current
    DESCRIPTION "."
    ::= { titanEdgeEncoderSchedulerAlarmSystemEthernetUnknownOffMonitors 2 }

titanEdgeEncoderSchedulerAlarmSystemEthernetUnknownOffName OBJECT-TYPE
    SYNTAX DisplayString
    MAX-ACCESS read-only
    STATUS current
    DESCRIPTION "."
    ::= { titanEdgeEncoderSchedulerAlarmSystemEthernetUnknownOffMonitors 2 }

titanEdgeEncoderSchedulerAlarmChannelLostOnNotification NOTIFICATION-TYPE
    OBJECTS {
        titanEdgeEncoderSchedulerAlarmChannelLostOnId
    }
    STATUS current
    DESCRIPTION "Channel is lost"
    ::= { titanEdgeEncoderSchedulerAlarmChannelLostOn 1 }

titanEdgeEncoderSchedulerAlarmChannelLostOnId OBJECT-TYPE
    SYNTAX DisplayString
    MAX-ACCESS read-only
    STATUS current
    DESCRIPTION "."
    ::= { titanEdgeEncoderSchedulerAlarmChannelLostOn 1 2 }

titanEdgeEncoderSchedulerAlarmChannelLostOffNotification NOTIFICATION-TYPE
    OBJECTS {
        titanEdgeEncoderSchedulerAlarmChannelLostOffId
    }
    STATUS current
    DESCRIPTION "Channel is lost"
    ::= { titanEdgeEncoderSchedulerAlarmChannelLostOn 2 }

titanEdgeEncoderSchedulerAlarmChannelLostOffId OBJECT-TYPE
    SYNTAX DisplayString
    MAX-ACCESS read-only
    STATUS current
    DESCRIPTION "."
    ::= { titanEdgeEncoderSchedulerAlarmChannelLostOffMonitors 2 }

titanEdgeEncoderSchedulerAlarmOutputDiscardedPacketsOnNotification NOTIFICATION-TYPE
    OBJECTS {
        titanEdgeEncoderSchedulerAlarmOutputDiscardedPacketsOnId,
        titanEdgeEncoderSchedulerAlarmOutputDiscardedPacketsOnIndex
    }
    STATUS current
    DESCRIPTION "Discarded Packet"
    ::= { titanEdgeEncoderSchedulerAlarmOutputDiscardedPacketsOn 1 }

titanEdgeEncoderSchedulerAlarmOutputDiscardedPacketsOnId OBJECT-TYPE
    SYNTAX DisplayString
    MAX-ACCESS read-only
    STATUS current
    DESCRIPTION "."
    ::= { titanEdgeEncoderSchedulerAlarmOutputDiscardedPacketsOn 1 2 }

titanEdgeEncoderSchedulerAlarmOutputDiscardedPacketsOnIndex OBJECT-TYPE
    SYNTAX DisplayString
    MAX-ACCESS read-only
    STATUS current
    DESCRIPTION "."
    ::= { titanEdgeEncoderSchedulerAlarmOutputDiscardedPacketsOn 1 2 }

titanEdgeEncoderSchedulerAlarmOutputDiscardedPacketsOffNotification NOTIFICATION-TYPE
    OBJECTS {
        titanEdgeEncoderSchedulerAlarmOutputDiscardedPacketsOffId,
        titanEdgeEncoderSchedulerAlarmOutputDiscardedPacketsOffIndex
    }
    STATUS current
    DESCRIPTION "Discarded Packet"
    ::= { titanEdgeEncoderSchedulerAlarmOutputDiscardedPacketsOn 2 }

titanEdgeEncoderSchedulerAlarmOutputDiscardedPacketsOffId OBJECT-TYPE
    SYNTAX DisplayString
    MAX-ACCESS read-only
    STATUS current
    DESCRIPTION "."
    ::= { titanEdgeEncoderSchedulerAlarmOutputDiscardedPacketsOffMonitors 2 }

titanEdgeEncoderSchedulerAlarmOutputDiscardedPacketsOffIndex OBJECT-TYPE
    SYNTAX DisplayString
    MAX-ACCESS read-only
    STATUS current
    DESCRIPTION "."
    ::= { titanEdgeEncoderSchedulerAlarmOutputDiscardedPacketsOffMonitors 2 }

titanEdgeEncoderSchedulerAlarmTsNoOutputConnectionOnNotification NOTIFICATION-TYPE
    OBJECTS {
        titanEdgeEncoderSchedulerAlarmTsNoOutputConnectionOnId,
        titanEdgeEncoderSchedulerAlarmTsNoOutputConnectionOnIndex
    }
    STATUS current
    DESCRIPTION "No TS output connected"
    ::= { titanEdgeEncoderSchedulerAlarmTsNoOutputConnectionOn 1 }

titanEdgeEncoderSchedulerAlarmTsNoOutputConnectionOnId OBJECT-TYPE
    SYNTAX DisplayString
    MAX-ACCESS read-only
    STATUS current
    DESCRIPTION "."
    ::= { titanEdgeEncoderSchedulerAlarmTsNoOutputConnectionOn 1 2 }

titanEdgeEncoderSchedulerAlarmTsNoOutputConnectionOnIndex OBJECT-TYPE
    SYNTAX DisplayString
    MAX-ACCESS read-only
    STATUS current
    DESCRIPTION "."
    ::= { titanEdgeEncoderSchedulerAlarmTsNoOutputConnectionOn 1 2 }

titanEdgeEncoderSchedulerAlarmTsNoOutputConnectionOffNotification NOTIFICATION-TYPE
    OBJECTS {
        titanEdgeEncoderSchedulerAlarmTsNoOutputConnectionOffId,
        titanEdgeEncoderSchedulerAlarmTsNoOutputConnectionOffIndex
    }
    STATUS current
    DESCRIPTION "No TS output connected"
    ::= { titanEdgeEncoderSchedulerAlarmTsNoOutputConnectionOn 2 }

titanEdgeEncoderSchedulerAlarmTsNoOutputConnectionOffId OBJECT-TYPE
    SYNTAX DisplayString
    MAX-ACCESS read-only
    STATUS current
    DESCRIPTION "."
    ::= { titanEdgeEncoderSchedulerAlarmTsNoOutputConnectionOffMonitors 2 }

titanEdgeEncoderSchedulerAlarmTsNoOutputConnectionOffIndex OBJECT-TYPE
    SYNTAX DisplayString
    MAX-ACCESS read-only
    STATUS current
    DESCRIPTION "."
    ::= { titanEdgeEncoderSchedulerAlarmTsNoOutputConnectionOffMonitors 2 }

titanEdgeEncoderSchedulerAlarmOutputBitrateInvalidOnNotification NOTIFICATION-TYPE
    OBJECTS {
        titanEdgeEncoderSchedulerAlarmOutputBitrateInvalidOnId,
        titanEdgeEncoderSchedulerAlarmOutputBitrateInvalidOnIndex
    }
    STATUS current
    DESCRIPTION "Bitrate is invalid for output"
    ::= { titanEdgeEncoderSchedulerAlarmOutputBitrateInvalidOn 1 }

titanEdgeEncoderSchedulerAlarmOutputBitrateInvalidOnId OBJECT-TYPE
    SYNTAX DisplayString
    MAX-ACCESS read-only
    STATUS current
    DESCRIPTION "."
    ::= { titanEdgeEncoderSchedulerAlarmOutputBitrateInvalidOn 1 2 }

titanEdgeEncoderSchedulerAlarmOutputBitrateInvalidOnIndex OBJECT-TYPE
    SYNTAX DisplayString
    MAX-ACCESS read-only
    STATUS current
    DESCRIPTION "."
    ::= { titanEdgeEncoderSchedulerAlarmOutputBitrateInvalidOn 1 2 }

titanEdgeEncoderSchedulerAlarmOutputBitrateInvalidOffNotification NOTIFICATION-TYPE
    OBJECTS {
        titanEdgeEncoderSchedulerAlarmOutputBitrateInvalidOffId,
        titanEdgeEncoderSchedulerAlarmOutputBitrateInvalidOffIndex
    }
    STATUS current
    DESCRIPTION "Bitrate is invalid for output"
    ::= { titanEdgeEncoderSchedulerAlarmOutputBitrateInvalidOn 2 }

titanEdgeEncoderSchedulerAlarmOutputBitrateInvalidOffId OBJECT-TYPE
    SYNTAX DisplayString
    MAX-ACCESS read-only
    STATUS current
    DESCRIPTION "."
    ::= { titanEdgeEncoderSchedulerAlarmOutputBitrateInvalidOffMonitors 2 }

titanEdgeEncoderSchedulerAlarmOutputBitrateInvalidOffIndex OBJECT-TYPE
    SYNTAX DisplayString
    MAX-ACCESS read-only
    STATUS current
    DESCRIPTION "."
    ::= { titanEdgeEncoderSchedulerAlarmOutputBitrateInvalidOffMonitors 2 }

titanEdgeEncoderProcessingLogProcessingFailureNotification NOTIFICATION-TYPE
    OBJECTS {
        titanEdgeEncoderProcessingLogProcessingFailureId
    }
    STATUS current
    DESCRIPTION "Processing failure"
    ::= { titanEdgeEncoderProcessingLogs 9 }

titanEdgeEncoderProcessingLogProcessingFailureId OBJECT-TYPE
    SYNTAX DisplayString
    MAX-ACCESS read-only
    STATUS current
    DESCRIPTION "."
    ::= { titanEdgeEncoderProcessingLogs 9 2 }

titanEdgeGatewayApiLogChannelAddedNotification NOTIFICATION-TYPE
    OBJECTS {
        titanEdgeGatewayApiLogChannelAddedId
    }
    STATUS current
    DESCRIPTION "Channel added"
    ::= { titanEdgeGatewayApiLogs 4 }

titanEdgeGatewayApiLogChannelAddedId OBJECT-TYPE
    SYNTAX DisplayString
    MAX-ACCESS read-only
    STATUS current
    DESCRIPTION "."
    ::= { titanEdgeGatewayApiLogs 4 2 }

titanEdgeGatewayApiLogChannelDeletedNotification NOTIFICATION-TYPE
    OBJECTS {
        titanEdgeGatewayApiLogChannelDeletedId
    }
    STATUS current
    DESCRIPTION "Channel deleted"
    ::= { titanEdgeGatewayApiLogs 5 }

titanEdgeGatewayApiLogChannelDeletedId OBJECT-TYPE
    SYNTAX DisplayString
    MAX-ACCESS read-only
    STATUS current
    DESCRIPTION "."
    ::= { titanEdgeGatewayApiLogs 5 2 }

titanEdgeGatewayApiLogChannelModifiedNotification NOTIFICATION-TYPE
    OBJECTS {
        titanEdgeGatewayApiLogChannelModifiedId
    }
    STATUS current
    DESCRIPTION "Channel modified"
    ::= { titanEdgeGatewayApiLogs 6 }

titanEdgeGatewayApiLogChannelModifiedId OBJECT-TYPE
    SYNTAX DisplayString
    MAX-ACCESS read-only
    STATUS current
    DESCRIPTION "."
    ::= { titanEdgeGatewayApiLogs 6 2 }

titanEdgeGatewaySchedulerLogChannelStartedNotification NOTIFICATION-TYPE
    OBJECTS {
        titanEdgeGatewaySchedulerLogChannelStartedId
    }
    STATUS current
    DESCRIPTION "Channel started"
    ::= { titanEdgeGatewaySchedulerLogs 7 }

titanEdgeGatewaySchedulerLogChannelStartedId OBJECT-TYPE
    SYNTAX DisplayString
    MAX-ACCESS read-only
    STATUS current
    DESCRIPTION "."
    ::= { titanEdgeGatewaySchedulerLogs 7 2 }

titanEdgeGatewaySchedulerLogChannelStoppedNotification NOTIFICATION-TYPE
    OBJECTS {
        titanEdgeGatewaySchedulerLogChannelStoppedId
    }
    STATUS current
    DESCRIPTION "Channel stopped"
    ::= { titanEdgeGatewaySchedulerLogs 8 }

titanEdgeGatewaySchedulerLogChannelStoppedId OBJECT-TYPE
    SYNTAX DisplayString
    MAX-ACCESS read-only
    STATUS current
    DESCRIPTION "."
    ::= { titanEdgeGatewaySchedulerLogs 8 2 }

titanEdgeGatewaySchedulerLogChannelFailoverInputChangedNotification NOTIFICATION-TYPE
    OBJECTS {
        titanEdgeGatewaySchedulerLogChannelFailoverInputChangedId,
        titanEdgeGatewaySchedulerLogChannelFailoverInputChangedIndex
    }
    STATUS current
    DESCRIPTION "Channel failover input changed"
    ::= { titanEdgeGatewaySchedulerLogs 10 }

titanEdgeGatewaySchedulerLogChannelFailoverInputChangedId OBJECT-TYPE
    SYNTAX DisplayString
    MAX-ACCESS read-only
    STATUS current
    DESCRIPTION "."
    ::= { titanEdgeGatewaySchedulerLogs 10 2 }

titanEdgeGatewaySchedulerLogChannelFailoverInputChangedIndex OBJECT-TYPE
    SYNTAX DisplayString
    MAX-ACCESS read-only
    STATUS current
    DESCRIPTION "."
    ::= { titanEdgeGatewaySchedulerLogs 10 2 }

titanEdgeGatewaySchedulerAlarmTsInputSignalMissingOnNotification NOTIFICATION-TYPE
    OBJECTS {
        titanEdgeGatewaySchedulerAlarmTsInputSignalMissingOnId,
        titanEdgeGatewaySchedulerAlarmTsInputSignalMissingOnIndex
    }
    STATUS current
    DESCRIPTION "TS input signal missing"
    ::= { titanEdgeGatewaySchedulerAlarmTsInputSignalMissingOn 1 }

titanEdgeGatewaySchedulerAlarmTsInputSignalMissingOnId OBJECT-TYPE
    SYNTAX DisplayString
    MAX-ACCESS read-only
    STATUS current
    DESCRIPTION "."
    ::= { titanEdgeGatewaySchedulerAlarmTsInputSignalMissingOn 1 2 }

titanEdgeGatewaySchedulerAlarmTsInputSignalMissingOnIndex OBJECT-TYPE
    SYNTAX DisplayString
    MAX-ACCESS read-only
    STATUS current
    DESCRIPTION "."
    ::= { titanEdgeGatewaySchedulerAlarmTsInputSignalMissingOn 1 2 }

titanEdgeGatewaySchedulerAlarmTsInputSignalMissingOffNotification NOTIFICATION-TYPE
    OBJECTS {
        titanEdgeGatewaySchedulerAlarmTsInputSignalMissingOffId,
        titanEdgeGatewaySchedulerAlarmTsInputSignalMissingOffIndex
    }
    STATUS current
    DESCRIPTION "TS input signal missing"
    ::= { titanEdgeGatewaySchedulerAlarmTsInputSignalMissingOn 2 }

titanEdgeGatewaySchedulerAlarmTsInputSignalMissingOffId OBJECT-TYPE
    SYNTAX DisplayString
    MAX-ACCESS read-only
    STATUS current
    DESCRIPTION "."
    ::= { titanEdgeGatewaySchedulerAlarmTsInputSignalMissingOffMonitors 2 }

titanEdgeGatewaySchedulerAlarmTsInputSignalMissingOffIndex OBJECT-TYPE
    SYNTAX DisplayString
    MAX-ACCESS read-only
    STATUS current
    DESCRIPTION "."
    ::= { titanEdgeGatewaySchedulerAlarmTsInputSignalMissingOffMonitors 2 }

titanEdgeGatewaySchedulerAlarmSatelliteInputSignalNotLockedOnNotification NOTIFICATION-TYPE
    OBJECTS {
        titanEdgeGatewaySchedulerAlarmSatelliteInputSignalNotLockedOnId,
        titanEdgeGatewaySchedulerAlarmSatelliteInputSignalNotLockedOnIndex
    }
    STATUS current
    DESCRIPTION "Satellite input signal not locked"
    ::= { titanEdgeGatewaySchedulerAlarmSatelliteInputSignalNotLockedOn 1 }

titanEdgeGatewaySchedulerAlarmSatelliteInputSignalNotLockedOnId OBJECT-TYPE
    SYNTAX DisplayString
    MAX-ACCESS read-only
    STATUS current
    DESCRIPTION "."
    ::= { titanEdgeGatewaySchedulerAlarmSatelliteInputSignalNotLockedOn 1 2 }

titanEdgeGatewaySchedulerAlarmSatelliteInputSignalNotLockedOnIndex OBJECT-TYPE
    SYNTAX DisplayString
    MAX-ACCESS read-only
    STATUS current
    DESCRIPTION "."
    ::= { titanEdgeGatewaySchedulerAlarmSatelliteInputSignalNotLockedOn 1 2 }

titanEdgeGatewaySchedulerAlarmSatelliteInputSignalNotLockedOffNotification NOTIFICATION-TYPE
    OBJECTS {
        titanEdgeGatewaySchedulerAlarmSatelliteInputSignalNotLockedOffId,
        titanEdgeGatewaySchedulerAlarmSatelliteInputSignalNotLockedOffIndex
    }
    STATUS current
    DESCRIPTION "Satellite input signal not locked"
    ::= { titanEdgeGatewaySchedulerAlarmSatelliteInputSignalNotLockedOn 2 }

titanEdgeGatewaySchedulerAlarmSatelliteInputSignalNotLockedOffId OBJECT-TYPE
    SYNTAX DisplayString
    MAX-ACCESS read-only
    STATUS current
    DESCRIPTION "."
    ::= { titanEdgeGatewaySchedulerAlarmSatelliteInputSignalNotLockedOffMonitors 2 }

titanEdgeGatewaySchedulerAlarmSatelliteInputSignalNotLockedOffIndex OBJECT-TYPE
    SYNTAX DisplayString
    MAX-ACCESS read-only
    STATUS current
    DESCRIPTION "."
    ::= { titanEdgeGatewaySchedulerAlarmSatelliteInputSignalNotLockedOffMonitors 2 }

titanEdgeGatewaySchedulerAlarmZixiInputNotConnectedOnNotification NOTIFICATION-TYPE
    OBJECTS {
        titanEdgeGatewaySchedulerAlarmZixiInputNotConnectedOnId,
        titanEdgeGatewaySchedulerAlarmZixiInputNotConnectedOnIndex
    }
    STATUS current
    DESCRIPTION "Zixi input not connected"
    ::= { titanEdgeGatewaySchedulerAlarmZixiInputNotConnectedOn 1 }

titanEdgeGatewaySchedulerAlarmZixiInputNotConnectedOnId OBJECT-TYPE
    SYNTAX DisplayString
    MAX-ACCESS read-only
    STATUS current
    DESCRIPTION "."
    ::= { titanEdgeGatewaySchedulerAlarmZixiInputNotConnectedOn 1 2 }

titanEdgeGatewaySchedulerAlarmZixiInputNotConnectedOnIndex OBJECT-TYPE
    SYNTAX DisplayString
    MAX-ACCESS read-only
    STATUS current
    DESCRIPTION "."
    ::= { titanEdgeGatewaySchedulerAlarmZixiInputNotConnectedOn 1 2 }

titanEdgeGatewaySchedulerAlarmZixiInputNotConnectedOffNotification NOTIFICATION-TYPE
    OBJECTS {
        titanEdgeGatewaySchedulerAlarmZixiInputNotConnectedOffId,
        titanEdgeGatewaySchedulerAlarmZixiInputNotConnectedOffIndex
    }
    STATUS current
    DESCRIPTION "Zixi input not connected"
    ::= { titanEdgeGatewaySchedulerAlarmZixiInputNotConnectedOn 2 }

titanEdgeGatewaySchedulerAlarmZixiInputNotConnectedOffId OBJECT-TYPE
    SYNTAX DisplayString
    MAX-ACCESS read-only
    STATUS current
    DESCRIPTION "."
    ::= { titanEdgeGatewaySchedulerAlarmZixiInputNotConnectedOffMonitors 2 }

titanEdgeGatewaySchedulerAlarmZixiInputNotConnectedOffIndex OBJECT-TYPE
    SYNTAX DisplayString
    MAX-ACCESS read-only
    STATUS current
    DESCRIPTION "."
    ::= { titanEdgeGatewaySchedulerAlarmZixiInputNotConnectedOffMonitors 2 }

titanEdgeGatewaySchedulerAlarmZixiExcessiveJitterOnNotification NOTIFICATION-TYPE
    OBJECTS {
        titanEdgeGatewaySchedulerAlarmZixiExcessiveJitterOnId,
        titanEdgeGatewaySchedulerAlarmZixiExcessiveJitterOnIndex,
        titanEdgeGatewaySchedulerAlarmZixiExcessiveJitterOnThreshold
    }
    STATUS current
    DESCRIPTION "Excessive Zixi input jitter"
    ::= { titanEdgeGatewaySchedulerAlarmZixiExcessiveJitterOn 1 }

titanEdgeGatewaySchedulerAlarmZixiExcessiveJitterOnId OBJECT-TYPE
    SYNTAX DisplayString
    MAX-ACCESS read-only
    STATUS current
    DESCRIPTION "."
    ::= { titanEdgeGatewaySchedulerAlarmZixiExcessiveJitterOn 1 2 }

titanEdgeGatewaySchedulerAlarmZixiExcessiveJitterOnIndex OBJECT-TYPE
    SYNTAX DisplayString
    MAX-ACCESS read-only
    STATUS current
    DESCRIPTION "."
    ::= { titanEdgeGatewaySchedulerAlarmZixiExcessiveJitterOn 1 2 }

titanEdgeGatewaySchedulerAlarmZixiExcessiveJitterOnThreshold OBJECT-TYPE
    SYNTAX INTEGER
    MAX-ACCESS read-only
    STATUS current
    DESCRIPTION "."
    ::= { titanEdgeGatewaySchedulerAlarmZixiExcessiveJitterOn 1 3 }

titanEdgeGatewaySchedulerAlarmZixiExcessiveJitterOffNotification NOTIFICATION-TYPE
    OBJECTS {
        titanEdgeGatewaySchedulerAlarmZixiExcessiveJitterOffId,
        titanEdgeGatewaySchedulerAlarmZixiExcessiveJitterOffIndex,
        titanEdgeGatewaySchedulerAlarmZixiExcessiveJitterOffThreshold
    }
    STATUS current
    DESCRIPTION "Excessive Zixi input jitter"
    ::= { titanEdgeGatewaySchedulerAlarmZixiExcessiveJitterOn 2 }

titanEdgeGatewaySchedulerAlarmZixiExcessiveJitterOffId OBJECT-TYPE
    SYNTAX DisplayString
    MAX-ACCESS read-only
    STATUS current
    DESCRIPTION "."
    ::= { titanEdgeGatewaySchedulerAlarmZixiExcessiveJitterOffMonitors 2 }

titanEdgeGatewaySchedulerAlarmZixiExcessiveJitterOffIndex OBJECT-TYPE
    SYNTAX DisplayString
    MAX-ACCESS read-only
    STATUS current
    DESCRIPTION "."
    ::= { titanEdgeGatewaySchedulerAlarmZixiExcessiveJitterOffMonitors 2 }

titanEdgeGatewaySchedulerAlarmZixiExcessiveJitterOffThreshold OBJECT-TYPE
    SYNTAX INTEGER
    MAX-ACCESS read-only
    STATUS current
    DESCRIPTION "."
    ::= { titanEdgeGatewaySchedulerAlarmZixiExcessiveJitterOffMonitors 3 }

titanEdgeGatewaySchedulerAlarmLicenseMissingOnNotification NOTIFICATION-TYPE
    OBJECTS {
        titanEdgeGatewaySchedulerAlarmLicenseMissingOnId,
        titanEdgeGatewaySchedulerAlarmLicenseMissingOnName
    }
    STATUS current
    DESCRIPTION "License Missing"
    ::= { titanEdgeGatewaySchedulerAlarmLicenseMissingOn 1 }

titanEdgeGatewaySchedulerAlarmLicenseMissingOnId OBJECT-TYPE
    SYNTAX DisplayString
    MAX-ACCESS read-only
    STATUS current
    DESCRIPTION "."
    ::= { titanEdgeGatewaySchedulerAlarmLicenseMissingOn 1 2 }

titanEdgeGatewaySchedulerAlarmLicenseMissingOnName OBJECT-TYPE
    SYNTAX DisplayString
    MAX-ACCESS read-only
    STATUS current
    DESCRIPTION "."
    ::= { titanEdgeGatewaySchedulerAlarmLicenseMissingOn 1 2 }

titanEdgeGatewaySchedulerAlarmLicenseMissingOffNotification NOTIFICATION-TYPE
    OBJECTS {
        titanEdgeGatewaySchedulerAlarmLicenseMissingOffId,
        titanEdgeGatewaySchedulerAlarmLicenseMissingOffName
    }
    STATUS current
    DESCRIPTION "License Missing"
    ::= { titanEdgeGatewaySchedulerAlarmLicenseMissingOn 2 }

titanEdgeGatewaySchedulerAlarmLicenseMissingOffId OBJECT-TYPE
    SYNTAX DisplayString
    MAX-ACCESS read-only
    STATUS current
    DESCRIPTION "."
    ::= { titanEdgeGatewaySchedulerAlarmLicenseMissingOffMonitors 2 }

titanEdgeGatewaySchedulerAlarmLicenseMissingOffName OBJECT-TYPE
    SYNTAX DisplayString
    MAX-ACCESS read-only
    STATUS current
    DESCRIPTION "."
    ::= { titanEdgeGatewaySchedulerAlarmLicenseMissingOffMonitors 2 }

titanEdgeGatewaySchedulerAlarmChannelInternalErrorOnNotification NOTIFICATION-TYPE
    OBJECTS {
        titanEdgeGatewaySchedulerAlarmChannelInternalErrorOnId
    }
    STATUS current
    DESCRIPTION "Channel internal error"
    ::= { titanEdgeGatewaySchedulerAlarmChannelInternalErrorOn 1 }

titanEdgeGatewaySchedulerAlarmChannelInternalErrorOnId OBJECT-TYPE
    SYNTAX DisplayString
    MAX-ACCESS read-only
    STATUS current
    DESCRIPTION "."
    ::= { titanEdgeGatewaySchedulerAlarmChannelInternalErrorOn 1 2 }

titanEdgeGatewaySchedulerAlarmChannelInternalErrorOffNotification NOTIFICATION-TYPE
    OBJECTS {
        titanEdgeGatewaySchedulerAlarmChannelInternalErrorOffId
    }
    STATUS current
    DESCRIPTION "Channel internal error"
    ::= { titanEdgeGatewaySchedulerAlarmChannelInternalErrorOn 2 }

titanEdgeGatewaySchedulerAlarmChannelInternalErrorOffId OBJECT-TYPE
    SYNTAX DisplayString
    MAX-ACCESS read-only
    STATUS current
    DESCRIPTION "."
    ::= { titanEdgeGatewaySchedulerAlarmChannelInternalErrorOffMonitors 2 }

titanEdgeGatewaySchedulerAlarmSystemExtensionPinUnknownOnNotification NOTIFICATION-TYPE
    OBJECTS {
        titanEdgeGatewaySchedulerAlarmSystemExtensionPinUnknownOnId,
        titanEdgeGatewaySchedulerAlarmSystemExtensionPinUnknownOnIndex
    }
    STATUS current
    DESCRIPTION "Hardware extension pin unknown"
    ::= { titanEdgeGatewaySchedulerAlarmSystemExtensionPinUnknownOn 1 }

titanEdgeGatewaySchedulerAlarmSystemExtensionPinUnknownOnId OBJECT-TYPE
    SYNTAX DisplayString
    MAX-ACCESS read-only
    STATUS current
    DESCRIPTION "."
    ::= { titanEdgeGatewaySchedulerAlarmSystemExtensionPinUnknownOn 1 2 }

titanEdgeGatewaySchedulerAlarmSystemExtensionPinUnknownOnIndex OBJECT-TYPE
    SYNTAX DisplayString
    MAX-ACCESS read-only
    STATUS current
    DESCRIPTION "."
    ::= { titanEdgeGatewaySchedulerAlarmSystemExtensionPinUnknownOn 1 2 }

titanEdgeGatewaySchedulerAlarmSystemExtensionPinUnknownOffNotification NOTIFICATION-TYPE
    OBJECTS {
        titanEdgeGatewaySchedulerAlarmSystemExtensionPinUnknownOffId,
        titanEdgeGatewaySchedulerAlarmSystemExtensionPinUnknownOffIndex
    }
    STATUS current
    DESCRIPTION "Hardware extension pin unknown"
    ::= { titanEdgeGatewaySchedulerAlarmSystemExtensionPinUnknownOn 2 }

titanEdgeGatewaySchedulerAlarmSystemExtensionPinUnknownOffId OBJECT-TYPE
    SYNTAX DisplayString
    MAX-ACCESS read-only
    STATUS current
    DESCRIPTION "."
    ::= { titanEdgeGatewaySchedulerAlarmSystemExtensionPinUnknownOffMonitors 2 }

titanEdgeGatewaySchedulerAlarmSystemExtensionPinUnknownOffIndex OBJECT-TYPE
    SYNTAX DisplayString
    MAX-ACCESS read-only
    STATUS current
    DESCRIPTION "."
    ::= { titanEdgeGatewaySchedulerAlarmSystemExtensionPinUnknownOffMonitors 2 }

titanEdgeGatewaySchedulerAlarmSystemExtensionPinInConflictOnNotification NOTIFICATION-TYPE
    OBJECTS {
        titanEdgeGatewaySchedulerAlarmSystemExtensionPinInConflictOnId,
        titanEdgeGatewaySchedulerAlarmSystemExtensionPinInConflictOnIndex
    }
    STATUS current
    DESCRIPTION "Hardware extension pin in conflict"
    ::= { titanEdgeGatewaySchedulerAlarmSystemExtensionPinInConflictOn 1 }

titanEdgeGatewaySchedulerAlarmSystemExtensionPinInConflictOnId OBJECT-TYPE
    SYNTAX DisplayString
    MAX-ACCESS read-only
    STATUS current
    DESCRIPTION "."
    ::= { titanEdgeGatewaySchedulerAlarmSystemExtensionPinInConflictOn 1 2 }

titanEdgeGatewaySchedulerAlarmSystemExtensionPinInConflictOnIndex OBJECT-TYPE
    SYNTAX DisplayString
    MAX-ACCESS read-only
    STATUS current
    DESCRIPTION "."
    ::= { titanEdgeGatewaySchedulerAlarmSystemExtensionPinInConflictOn 1 2 }

titanEdgeGatewaySchedulerAlarmSystemExtensionPinInConflictOffNotification NOTIFICATION-TYPE
    OBJECTS {
        titanEdgeGatewaySchedulerAlarmSystemExtensionPinInConflictOffId,
        titanEdgeGatewaySchedulerAlarmSystemExtensionPinInConflictOffIndex
    }
    STATUS current
    DESCRIPTION "Hardware extension pin in conflict"
    ::= { titanEdgeGatewaySchedulerAlarmSystemExtensionPinInConflictOn 2 }

titanEdgeGatewaySchedulerAlarmSystemExtensionPinInConflictOffId OBJECT-TYPE
    SYNTAX DisplayString
    MAX-ACCESS read-only
    STATUS current
    DESCRIPTION "."
    ::= { titanEdgeGatewaySchedulerAlarmSystemExtensionPinInConflictOffMonitors 2 }

titanEdgeGatewaySchedulerAlarmSystemExtensionPinInConflictOffIndex OBJECT-TYPE
    SYNTAX DisplayString
    MAX-ACCESS read-only
    STATUS current
    DESCRIPTION "."
    ::= { titanEdgeGatewaySchedulerAlarmSystemExtensionPinInConflictOffMonitors 2 }

titanEdgeGatewaySchedulerAlarmSystemExtensionPinConfigurationInvalidOnNotification NOTIFICATION-TYPE
    OBJECTS {
        titanEdgeGatewaySchedulerAlarmSystemExtensionPinConfigurationInvalidOnId,
        titanEdgeGatewaySchedulerAlarmSystemExtensionPinConfigurationInvalidOnIndex
    }
    STATUS current
    DESCRIPTION "Hardware extension pin configuration invalid"
    ::= { titanEdgeGatewaySchedulerAlarmSystemExtensionPinConfigurationInvalidOn 1 }

titanEdgeGatewaySchedulerAlarmSystemExtensionPinConfigurationInvalidOnId OBJECT-TYPE
    SYNTAX DisplayString
    MAX-ACCESS read-only
    STATUS current
    DESCRIPTION "."
    ::= { titanEdgeGatewaySchedulerAlarmSystemExtensionPinConfigurationInvalidOn 1 2 }

titanEdgeGatewaySchedulerAlarmSystemExtensionPinConfigurationInvalidOnIndex OBJECT-TYPE
    SYNTAX DisplayString
    MAX-ACCESS read-only
    STATUS current
    DESCRIPTION "."
    ::= { titanEdgeGatewaySchedulerAlarmSystemExtensionPinConfigurationInvalidOn 1 2 }

titanEdgeGatewaySchedulerAlarmSystemExtensionPinConfigurationInvalidOffNotification NOTIFICATION-TYPE
    OBJECTS {
        titanEdgeGatewaySchedulerAlarmSystemExtensionPinConfigurationInvalidOffId,
        titanEdgeGatewaySchedulerAlarmSystemExtensionPinConfigurationInvalidOffIndex
    }
    STATUS current
    DESCRIPTION "Hardware extension pin configuration invalid"
    ::= { titanEdgeGatewaySchedulerAlarmSystemExtensionPinConfigurationInvalidOn 2 }

titanEdgeGatewaySchedulerAlarmSystemExtensionPinConfigurationInvalidOffId OBJECT-TYPE
    SYNTAX DisplayString
    MAX-ACCESS read-only
    STATUS current
    DESCRIPTION "."
    ::= { titanEdgeGatewaySchedulerAlarmSystemExtensionPinConfigurationInvalidOffMonitors 2 }

titanEdgeGatewaySchedulerAlarmSystemExtensionPinConfigurationInvalidOffIndex OBJECT-TYPE
    SYNTAX DisplayString
    MAX-ACCESS read-only
    STATUS current
    DESCRIPTION "."
    ::= { titanEdgeGatewaySchedulerAlarmSystemExtensionPinConfigurationInvalidOffMonitors 2 }

titanEdgeGatewaySchedulerAlarmInternalInputNotConnectedOnNotification NOTIFICATION-TYPE
    OBJECTS {
        titanEdgeGatewaySchedulerAlarmInternalInputNotConnectedOnId,
        titanEdgeGatewaySchedulerAlarmInternalInputNotConnectedOnIndex
    }
    STATUS current
    DESCRIPTION "Internal input not connected"
    ::= { titanEdgeGatewaySchedulerAlarmInternalInputNotConnectedOn 1 }

titanEdgeGatewaySchedulerAlarmInternalInputNotConnectedOnId OBJECT-TYPE
    SYNTAX DisplayString
    MAX-ACCESS read-only
    STATUS current
    DESCRIPTION "."
    ::= { titanEdgeGatewaySchedulerAlarmInternalInputNotConnectedOn 1 2 }

titanEdgeGatewaySchedulerAlarmInternalInputNotConnectedOnIndex OBJECT-TYPE
    SYNTAX DisplayString
    MAX-ACCESS read-only
    STATUS current
    DESCRIPTION "."
    ::= { titanEdgeGatewaySchedulerAlarmInternalInputNotConnectedOn 1 2 }

titanEdgeGatewaySchedulerAlarmInternalInputNotConnectedOffNotification NOTIFICATION-TYPE
    OBJECTS {
        titanEdgeGatewaySchedulerAlarmInternalInputNotConnectedOffId,
        titanEdgeGatewaySchedulerAlarmInternalInputNotConnectedOffIndex
    }
    STATUS current
    DESCRIPTION "Internal input not connected"
    ::= { titanEdgeGatewaySchedulerAlarmInternalInputNotConnectedOn 2 }

titanEdgeGatewaySchedulerAlarmInternalInputNotConnectedOffId OBJECT-TYPE
    SYNTAX DisplayString
    MAX-ACCESS read-only
    STATUS current
    DESCRIPTION "."
    ::= { titanEdgeGatewaySchedulerAlarmInternalInputNotConnectedOffMonitors 2 }

titanEdgeGatewaySchedulerAlarmInternalInputNotConnectedOffIndex OBJECT-TYPE
    SYNTAX DisplayString
    MAX-ACCESS read-only
    STATUS current
    DESCRIPTION "."
    ::= { titanEdgeGatewaySchedulerAlarmInternalInputNotConnectedOffMonitors 2 }

titanEdgeGatewaySchedulerAlarmTsSmpte20227SignalMissingOnNotification NOTIFICATION-TYPE
    OBJECTS {
        titanEdgeGatewaySchedulerAlarmTsSmpte20227SignalMissingOnId,
        titanEdgeGatewaySchedulerAlarmTsSmpte20227SignalMissingOnIndex,
        titanEdgeGatewaySchedulerAlarmTsSmpte20227SignalMissingOnName
    }
    STATUS current
    DESCRIPTION "SMPTE 2022-7 signal is missing"
    ::= { titanEdgeGatewaySchedulerAlarmTsSmpte20227SignalMissingOn 1 }

titanEdgeGatewaySchedulerAlarmTsSmpte20227SignalMissingOnId OBJECT-TYPE
    SYNTAX DisplayString
    MAX-ACCESS read-only
    STATUS current
    DESCRIPTION "."
    ::= { titanEdgeGatewaySchedulerAlarmTsSmpte20227SignalMissingOn 1 2 }

titanEdgeGatewaySchedulerAlarmTsSmpte20227SignalMissingOnIndex OBJECT-TYPE
    SYNTAX DisplayString
    MAX-ACCESS read-only
    STATUS current
    DESCRIPTION "."
    ::= { titanEdgeGatewaySchedulerAlarmTsSmpte20227SignalMissingOn 1 2 }

titanEdgeGatewaySchedulerAlarmTsSmpte20227SignalMissingOnName OBJECT-TYPE
    SYNTAX DisplayString
    MAX-ACCESS read-only
    STATUS current
    DESCRIPTION "."
    ::= { titanEdgeGatewaySchedulerAlarmTsSmpte20227SignalMissingOn 1 2 }

titanEdgeGatewaySchedulerAlarmTsSmpte20227SignalMissingOffNotification NOTIFICATION-TYPE
    OBJECTS {
        titanEdgeGatewaySchedulerAlarmTsSmpte20227SignalMissingOffId,
        titanEdgeGatewaySchedulerAlarmTsSmpte20227SignalMissingOffIndex,
        titanEdgeGatewaySchedulerAlarmTsSmpte20227SignalMissingOffName
    }
    STATUS current
    DESCRIPTION "SMPTE 2022-7 signal is missing"
    ::= { titanEdgeGatewaySchedulerAlarmTsSmpte20227SignalMissingOn 2 }

titanEdgeGatewaySchedulerAlarmTsSmpte20227SignalMissingOffId OBJECT-TYPE
    SYNTAX DisplayString
    MAX-ACCESS read-only
    STATUS current
    DESCRIPTION "."
    ::= { titanEdgeGatewaySchedulerAlarmTsSmpte20227SignalMissingOffMonitors 2 }

titanEdgeGatewaySchedulerAlarmTsSmpte20227SignalMissingOffIndex OBJECT-TYPE
    SYNTAX DisplayString
    MAX-ACCESS read-only
    STATUS current
    DESCRIPTION "."
    ::= { titanEdgeGatewaySchedulerAlarmTsSmpte20227SignalMissingOffMonitors 2 }

titanEdgeGatewaySchedulerAlarmTsSmpte20227SignalMissingOffName OBJECT-TYPE
    SYNTAX DisplayString
    MAX-ACCESS read-only
    STATUS current
    DESCRIPTION "."
    ::= { titanEdgeGatewaySchedulerAlarmTsSmpte20227SignalMissingOffMonitors 2 }

titanEdgeGatewaySchedulerAlarmTsSmpte20227SkewTooLargeOnNotification NOTIFICATION-TYPE
    OBJECTS {
        titanEdgeGatewaySchedulerAlarmTsSmpte20227SkewTooLargeOnId,
        titanEdgeGatewaySchedulerAlarmTsSmpte20227SkewTooLargeOnIndex
    }
    STATUS current
    DESCRIPTION "SMPTE 2022-7 skew is too large"
    ::= { titanEdgeGatewaySchedulerAlarmTsSmpte20227SkewTooLargeOn 1 }

titanEdgeGatewaySchedulerAlarmTsSmpte20227SkewTooLargeOnId OBJECT-TYPE
    SYNTAX DisplayString
    MAX-ACCESS read-only
    STATUS current
    DESCRIPTION "."
    ::= { titanEdgeGatewaySchedulerAlarmTsSmpte20227SkewTooLargeOn 1 2 }

titanEdgeGatewaySchedulerAlarmTsSmpte20227SkewTooLargeOnIndex OBJECT-TYPE
    SYNTAX DisplayString
    MAX-ACCESS read-only
    STATUS current
    DESCRIPTION "."
    ::= { titanEdgeGatewaySchedulerAlarmTsSmpte20227SkewTooLargeOn 1 2 }

titanEdgeGatewaySchedulerAlarmTsSmpte20227SkewTooLargeOffNotification NOTIFICATION-TYPE
    OBJECTS {
        titanEdgeGatewaySchedulerAlarmTsSmpte20227SkewTooLargeOffId,
        titanEdgeGatewaySchedulerAlarmTsSmpte20227SkewTooLargeOffIndex
    }
    STATUS current
    DESCRIPTION "SMPTE 2022-7 skew is too large"
    ::= { titanEdgeGatewaySchedulerAlarmTsSmpte20227SkewTooLargeOn 2 }

titanEdgeGatewaySchedulerAlarmTsSmpte20227SkewTooLargeOffId OBJECT-TYPE
    SYNTAX DisplayString
    MAX-ACCESS read-only
    STATUS current
    DESCRIPTION "."
    ::= { titanEdgeGatewaySchedulerAlarmTsSmpte20227SkewTooLargeOffMonitors 2 }

titanEdgeGatewaySchedulerAlarmTsSmpte20227SkewTooLargeOffIndex OBJECT-TYPE
    SYNTAX DisplayString
    MAX-ACCESS read-only
    STATUS current
    DESCRIPTION "."
    ::= { titanEdgeGatewaySchedulerAlarmTsSmpte20227SkewTooLargeOffMonitors 2 }

titanEdgeGatewaySchedulerAlarmSystemEthernetUnknownOnNotification NOTIFICATION-TYPE
    OBJECTS {
        titanEdgeGatewaySchedulerAlarmSystemEthernetUnknownOnId,
        titanEdgeGatewaySchedulerAlarmSystemEthernetUnknownOnIndex,
        titanEdgeGatewaySchedulerAlarmSystemEthernetUnknownOnName
    }
    STATUS current
    DESCRIPTION "Ethernet link unknown"
    ::= { titanEdgeGatewaySchedulerAlarmSystemEthernetUnknownOn 1 }

titanEdgeGatewaySchedulerAlarmSystemEthernetUnknownOnId OBJECT-TYPE
    SYNTAX DisplayString
    MAX-ACCESS read-only
    STATUS current
    DESCRIPTION "."
    ::= { titanEdgeGatewaySchedulerAlarmSystemEthernetUnknownOn 1 2 }

titanEdgeGatewaySchedulerAlarmSystemEthernetUnknownOnIndex OBJECT-TYPE
    SYNTAX DisplayString
    MAX-ACCESS read-only
    STATUS current
    DESCRIPTION "."
    ::= { titanEdgeGatewaySchedulerAlarmSystemEthernetUnknownOn 1 2 }

titanEdgeGatewaySchedulerAlarmSystemEthernetUnknownOnName OBJECT-TYPE
    SYNTAX DisplayString
    MAX-ACCESS read-only
    STATUS current
    DESCRIPTION "."
    ::= { titanEdgeGatewaySchedulerAlarmSystemEthernetUnknownOn 1 2 }

titanEdgeGatewaySchedulerAlarmSystemEthernetUnknownOffNotification NOTIFICATION-TYPE
    OBJECTS {
        titanEdgeGatewaySchedulerAlarmSystemEthernetUnknownOffId,
        titanEdgeGatewaySchedulerAlarmSystemEthernetUnknownOffIndex,
        titanEdgeGatewaySchedulerAlarmSystemEthernetUnknownOffName
    }
    STATUS current
    DESCRIPTION "Ethernet link unknown"
    ::= { titanEdgeGatewaySchedulerAlarmSystemEthernetUnknownOn 2 }

titanEdgeGatewaySchedulerAlarmSystemEthernetUnknownOffId OBJECT-TYPE
    SYNTAX DisplayString
    MAX-ACCESS read-only
    STATUS current
    DESCRIPTION "."
    ::= { titanEdgeGatewaySchedulerAlarmSystemEthernetUnknownOffMonitors 2 }

titanEdgeGatewaySchedulerAlarmSystemEthernetUnknownOffIndex OBJECT-TYPE
    SYNTAX DisplayString
    MAX-ACCESS read-only
    STATUS current
    DESCRIPTION "."
    ::= { titanEdgeGatewaySchedulerAlarmSystemEthernetUnknownOffMonitors 2 }

titanEdgeGatewaySchedulerAlarmSystemEthernetUnknownOffName OBJECT-TYPE
    SYNTAX DisplayString
    MAX-ACCESS read-only
    STATUS current
    DESCRIPTION "."
    ::= { titanEdgeGatewaySchedulerAlarmSystemEthernetUnknownOffMonitors 2 }

titanEdgeGatewaySchedulerAlarmCompositionProgramDescramblingPreventedOnNotification NOTIFICATION-TYPE
    OBJECTS {
        titanEdgeGatewaySchedulerAlarmCompositionProgramDescramblingPreventedOnId,
        titanEdgeGatewaySchedulerAlarmCompositionProgramDescramblingPreventedOnIndex
    }
    STATUS current
    DESCRIPTION "Program descrambling prevented"
    ::= { titanEdgeGatewaySchedulerAlarmCompositionProgramDescramblingPreventedOn 1 }

titanEdgeGatewaySchedulerAlarmCompositionProgramDescramblingPreventedOnId OBJECT-TYPE
    SYNTAX DisplayString
    MAX-ACCESS read-only
    STATUS current
    DESCRIPTION "."
    ::= { titanEdgeGatewaySchedulerAlarmCompositionProgramDescramblingPreventedOn 1 2 }

titanEdgeGatewaySchedulerAlarmCompositionProgramDescramblingPreventedOnIndex OBJECT-TYPE
    SYNTAX DisplayString
    MAX-ACCESS read-only
    STATUS current
    DESCRIPTION "."
    ::= { titanEdgeGatewaySchedulerAlarmCompositionProgramDescramblingPreventedOn 1 2 }

titanEdgeGatewaySchedulerAlarmCompositionProgramDescramblingPreventedOffNotification NOTIFICATION-TYPE
    OBJECTS {
        titanEdgeGatewaySchedulerAlarmCompositionProgramDescramblingPreventedOffId,
        titanEdgeGatewaySchedulerAlarmCompositionProgramDescramblingPreventedOffIndex
    }
    STATUS current
    DESCRIPTION "Program descrambling prevented"
    ::= { titanEdgeGatewaySchedulerAlarmCompositionProgramDescramblingPreventedOn 2 }

titanEdgeGatewaySchedulerAlarmCompositionProgramDescramblingPreventedOffId OBJECT-TYPE
    SYNTAX DisplayString
    MAX-ACCESS read-only
    STATUS current
    DESCRIPTION "."
    ::= { titanEdgeGatewaySchedulerAlarmCompositionProgramDescramblingPreventedOffMonitors 2 }

titanEdgeGatewaySchedulerAlarmCompositionProgramDescramblingPreventedOffIndex OBJECT-TYPE
    SYNTAX DisplayString
    MAX-ACCESS read-only
    STATUS current
    DESCRIPTION "."
    ::= { titanEdgeGatewaySchedulerAlarmCompositionProgramDescramblingPreventedOffMonitors 2 }

titanEdgeGatewaySchedulerAlarmChannelLostOnNotification NOTIFICATION-TYPE
    OBJECTS {
        titanEdgeGatewaySchedulerAlarmChannelLostOnId
    }
    STATUS current
    DESCRIPTION "Channel is lost"
    ::= { titanEdgeGatewaySchedulerAlarmChannelLostOn 1 }

titanEdgeGatewaySchedulerAlarmChannelLostOnId OBJECT-TYPE
    SYNTAX DisplayString
    MAX-ACCESS read-only
    STATUS current
    DESCRIPTION "."
    ::= { titanEdgeGatewaySchedulerAlarmChannelLostOn 1 2 }

titanEdgeGatewaySchedulerAlarmChannelLostOffNotification NOTIFICATION-TYPE
    OBJECTS {
        titanEdgeGatewaySchedulerAlarmChannelLostOffId
    }
    STATUS current
    DESCRIPTION "Channel is lost"
    ::= { titanEdgeGatewaySchedulerAlarmChannelLostOn 2 }

titanEdgeGatewaySchedulerAlarmChannelLostOffId OBJECT-TYPE
    SYNTAX DisplayString
    MAX-ACCESS read-only
    STATUS current
    DESCRIPTION "."
    ::= { titanEdgeGatewaySchedulerAlarmChannelLostOffMonitors 2 }

titanEdgeGatewaySchedulerAlarmOutputDiscardedPacketsOnNotification NOTIFICATION-TYPE
    OBJECTS {
        titanEdgeGatewaySchedulerAlarmOutputDiscardedPacketsOnId,
        titanEdgeGatewaySchedulerAlarmOutputDiscardedPacketsOnIndex
    }
    STATUS current
    DESCRIPTION "Discarded Packet"
    ::= { titanEdgeGatewaySchedulerAlarmOutputDiscardedPacketsOn 1 }

titanEdgeGatewaySchedulerAlarmOutputDiscardedPacketsOnId OBJECT-TYPE
    SYNTAX DisplayString
    MAX-ACCESS read-only
    STATUS current
    DESCRIPTION "."
    ::= { titanEdgeGatewaySchedulerAlarmOutputDiscardedPacketsOn 1 2 }

titanEdgeGatewaySchedulerAlarmOutputDiscardedPacketsOnIndex OBJECT-TYPE
    SYNTAX DisplayString
    MAX-ACCESS read-only
    STATUS current
    DESCRIPTION "."
    ::= { titanEdgeGatewaySchedulerAlarmOutputDiscardedPacketsOn 1 2 }

titanEdgeGatewaySchedulerAlarmOutputDiscardedPacketsOffNotification NOTIFICATION-TYPE
    OBJECTS {
        titanEdgeGatewaySchedulerAlarmOutputDiscardedPacketsOffId,
        titanEdgeGatewaySchedulerAlarmOutputDiscardedPacketsOffIndex
    }
    STATUS current
    DESCRIPTION "Discarded Packet"
    ::= { titanEdgeGatewaySchedulerAlarmOutputDiscardedPacketsOn 2 }

titanEdgeGatewaySchedulerAlarmOutputDiscardedPacketsOffId OBJECT-TYPE
    SYNTAX DisplayString
    MAX-ACCESS read-only
    STATUS current
    DESCRIPTION "."
    ::= { titanEdgeGatewaySchedulerAlarmOutputDiscardedPacketsOffMonitors 2 }

titanEdgeGatewaySchedulerAlarmOutputDiscardedPacketsOffIndex OBJECT-TYPE
    SYNTAX DisplayString
    MAX-ACCESS read-only
    STATUS current
    DESCRIPTION "."
    ::= { titanEdgeGatewaySchedulerAlarmOutputDiscardedPacketsOffMonitors 2 }

titanEdgeGatewaySchedulerAlarmCompositionRemuxRemappingDetectedOnNotification NOTIFICATION-TYPE
    OBJECTS {
        titanEdgeGatewaySchedulerAlarmCompositionRemuxRemappingDetectedOnId,
        titanEdgeGatewaySchedulerAlarmCompositionRemuxRemappingDetectedOnIndex
    }
    STATUS current
    DESCRIPTION "Remux has remapped the input content"
    ::= { titanEdgeGatewaySchedulerAlarmCompositionRemuxRemappingDetectedOn 1 }

titanEdgeGatewaySchedulerAlarmCompositionRemuxRemappingDetectedOnId OBJECT-TYPE
    SYNTAX DisplayString
    MAX-ACCESS read-only
    STATUS current
    DESCRIPTION "."
    ::= { titanEdgeGatewaySchedulerAlarmCompositionRemuxRemappingDetectedOn 1 2 }

titanEdgeGatewaySchedulerAlarmCompositionRemuxRemappingDetectedOnIndex OBJECT-TYPE
    SYNTAX INTEGER
    MAX-ACCESS read-only
    STATUS current
    DESCRIPTION "."
    ::= { titanEdgeGatewaySchedulerAlarmCompositionRemuxRemappingDetectedOn 1 2 }

titanEdgeGatewaySchedulerAlarmCompositionRemuxRemappingDetectedOffNotification NOTIFICATION-TYPE
    OBJECTS {
        titanEdgeGatewaySchedulerAlarmCompositionRemuxRemappingDetectedOffId,
        titanEdgeGatewaySchedulerAlarmCompositionRemuxRemappingDetectedOffIndex
    }
    STATUS current
    DESCRIPTION "Remux has remapped the input content"
    ::= { titanEdgeGatewaySchedulerAlarmCompositionRemuxRemappingDetectedOn 2 }

titanEdgeGatewaySchedulerAlarmCompositionRemuxRemappingDetectedOffId OBJECT-TYPE
    SYNTAX DisplayString
    MAX-ACCESS read-only
    STATUS current
    DESCRIPTION "."
    ::= { titanEdgeGatewaySchedulerAlarmCompositionRemuxRemappingDetectedOffMonitors 2 }

titanEdgeGatewaySchedulerAlarmCompositionRemuxRemappingDetectedOffIndex OBJECT-TYPE
    SYNTAX INTEGER
    MAX-ACCESS read-only
    STATUS current
    DESCRIPTION "."
    ::= { titanEdgeGatewaySchedulerAlarmCompositionRemuxRemappingDetectedOffMonitors 2 }

titanEdgeGatewaySchedulerAlarmCompositionRemuxInputsMissingActivityOnNotification NOTIFICATION-TYPE
    OBJECTS {
        titanEdgeGatewaySchedulerAlarmCompositionRemuxInputsMissingActivityOnId
    }
    STATUS current
    DESCRIPTION "Remux inputs missing activity"
    ::= { titanEdgeGatewaySchedulerAlarmCompositionRemuxInputsMissingActivityOn 1 }

titanEdgeGatewaySchedulerAlarmCompositionRemuxInputsMissingActivityOnId OBJECT-TYPE
    SYNTAX DisplayString
    MAX-ACCESS read-only
    STATUS current
    DESCRIPTION "."
    ::= { titanEdgeGatewaySchedulerAlarmCompositionRemuxInputsMissingActivityOn 1 2 }

titanEdgeGatewaySchedulerAlarmCompositionRemuxInputsMissingActivityOffNotification NOTIFICATION-TYPE
    OBJECTS {
        titanEdgeGatewaySchedulerAlarmCompositionRemuxInputsMissingActivityOffId
    }
    STATUS current
    DESCRIPTION "Remux inputs missing activity"
    ::= { titanEdgeGatewaySchedulerAlarmCompositionRemuxInputsMissingActivityOn 2 }

titanEdgeGatewaySchedulerAlarmCompositionRemuxInputsMissingActivityOffId OBJECT-TYPE
    SYNTAX DisplayString
    MAX-ACCESS read-only
    STATUS current
    DESCRIPTION "."
    ::= { titanEdgeGatewaySchedulerAlarmCompositionRemuxInputsMissingActivityOffMonitors 2 }

titanEdgeGatewaySchedulerAlarmCompositionRemuxLimitsReachedOnNotification NOTIFICATION-TYPE
    OBJECTS {
        titanEdgeGatewaySchedulerAlarmCompositionRemuxLimitsReachedOnId
    }
    STATUS current
    DESCRIPTION "Remux limits have been reached"
    ::= { titanEdgeGatewaySchedulerAlarmCompositionRemuxLimitsReachedOn 1 }

titanEdgeGatewaySchedulerAlarmCompositionRemuxLimitsReachedOnId OBJECT-TYPE
    SYNTAX DisplayString
    MAX-ACCESS read-only
    STATUS current
    DESCRIPTION "."
    ::= { titanEdgeGatewaySchedulerAlarmCompositionRemuxLimitsReachedOn 1 2 }

titanEdgeGatewaySchedulerAlarmCompositionRemuxLimitsReachedOffNotification NOTIFICATION-TYPE
    OBJECTS {
        titanEdgeGatewaySchedulerAlarmCompositionRemuxLimitsReachedOffId
    }
    STATUS current
    DESCRIPTION "Remux limits have been reached"
    ::= { titanEdgeGatewaySchedulerAlarmCompositionRemuxLimitsReachedOn 2 }

titanEdgeGatewaySchedulerAlarmCompositionRemuxLimitsReachedOffId OBJECT-TYPE
    SYNTAX DisplayString
    MAX-ACCESS read-only
    STATUS current
    DESCRIPTION "."
    ::= { titanEdgeGatewaySchedulerAlarmCompositionRemuxLimitsReachedOffMonitors 2 }

titanEdgeGatewaySchedulerAlarmTsNoOutputConnectionOnNotification NOTIFICATION-TYPE
    OBJECTS {
        titanEdgeGatewaySchedulerAlarmTsNoOutputConnectionOnId,
        titanEdgeGatewaySchedulerAlarmTsNoOutputConnectionOnIndex
    }
    STATUS current
    DESCRIPTION "No TS output connected"
    ::= { titanEdgeGatewaySchedulerAlarmTsNoOutputConnectionOn 1 }

titanEdgeGatewaySchedulerAlarmTsNoOutputConnectionOnId OBJECT-TYPE
    SYNTAX DisplayString
    MAX-ACCESS read-only
    STATUS current
    DESCRIPTION "."
    ::= { titanEdgeGatewaySchedulerAlarmTsNoOutputConnectionOn 1 2 }

titanEdgeGatewaySchedulerAlarmTsNoOutputConnectionOnIndex OBJECT-TYPE
    SYNTAX DisplayString
    MAX-ACCESS read-only
    STATUS current
    DESCRIPTION "."
    ::= { titanEdgeGatewaySchedulerAlarmTsNoOutputConnectionOn 1 2 }

titanEdgeGatewaySchedulerAlarmTsNoOutputConnectionOffNotification NOTIFICATION-TYPE
    OBJECTS {
        titanEdgeGatewaySchedulerAlarmTsNoOutputConnectionOffId,
        titanEdgeGatewaySchedulerAlarmTsNoOutputConnectionOffIndex
    }
    STATUS current
    DESCRIPTION "No TS output connected"
    ::= { titanEdgeGatewaySchedulerAlarmTsNoOutputConnectionOn 2 }

titanEdgeGatewaySchedulerAlarmTsNoOutputConnectionOffId OBJECT-TYPE
    SYNTAX DisplayString
    MAX-ACCESS read-only
    STATUS current
    DESCRIPTION "."
    ::= { titanEdgeGatewaySchedulerAlarmTsNoOutputConnectionOffMonitors 2 }

titanEdgeGatewaySchedulerAlarmTsNoOutputConnectionOffIndex OBJECT-TYPE
    SYNTAX DisplayString
    MAX-ACCESS read-only
    STATUS current
    DESCRIPTION "."
    ::= { titanEdgeGatewaySchedulerAlarmTsNoOutputConnectionOffMonitors 2 }

titanEdgeGatewaySchedulerAlarmCompositionMCamLimitsReachedOnNotification NOTIFICATION-TYPE
    OBJECTS {
        titanEdgeGatewaySchedulerAlarmCompositionMCamLimitsReachedOnId,
        titanEdgeGatewaySchedulerAlarmCompositionMCamLimitsReachedOnIndex,
        titanEdgeGatewaySchedulerAlarmCompositionMCamLimitsReachedOnName
    }
    STATUS current
    DESCRIPTION "M-CAM capacity has reached the limit set"
    ::= { titanEdgeGatewaySchedulerAlarmCompositionMCamLimitsReachedOn 1 }

titanEdgeGatewaySchedulerAlarmCompositionMCamLimitsReachedOnId OBJECT-TYPE
    SYNTAX DisplayString
    MAX-ACCESS read-only
    STATUS current
    DESCRIPTION "."
    ::= { titanEdgeGatewaySchedulerAlarmCompositionMCamLimitsReachedOn 1 2 }

titanEdgeGatewaySchedulerAlarmCompositionMCamLimitsReachedOnIndex OBJECT-TYPE
    SYNTAX DisplayString
    MAX-ACCESS read-only
    STATUS current
    DESCRIPTION "."
    ::= { titanEdgeGatewaySchedulerAlarmCompositionMCamLimitsReachedOn 1 2 }

titanEdgeGatewaySchedulerAlarmCompositionMCamLimitsReachedOnName OBJECT-TYPE
    SYNTAX DisplayString
    MAX-ACCESS read-only
    STATUS current
    DESCRIPTION "."
    ::= { titanEdgeGatewaySchedulerAlarmCompositionMCamLimitsReachedOn 1 2 }

titanEdgeGatewaySchedulerAlarmCompositionMCamLimitsReachedOffNotification NOTIFICATION-TYPE
    OBJECTS {
        titanEdgeGatewaySchedulerAlarmCompositionMCamLimitsReachedOffId,
        titanEdgeGatewaySchedulerAlarmCompositionMCamLimitsReachedOffIndex,
        titanEdgeGatewaySchedulerAlarmCompositionMCamLimitsReachedOffName
    }
    STATUS current
    DESCRIPTION "M-CAM capacity has reached the limit set"
    ::= { titanEdgeGatewaySchedulerAlarmCompositionMCamLimitsReachedOn 2 }

titanEdgeGatewaySchedulerAlarmCompositionMCamLimitsReachedOffId OBJECT-TYPE
    SYNTAX DisplayString
    MAX-ACCESS read-only
    STATUS current
    DESCRIPTION "."
    ::= { titanEdgeGatewaySchedulerAlarmCompositionMCamLimitsReachedOffMonitors 2 }

titanEdgeGatewaySchedulerAlarmCompositionMCamLimitsReachedOffIndex OBJECT-TYPE
    SYNTAX DisplayString
    MAX-ACCESS read-only
    STATUS current
    DESCRIPTION "."
    ::= { titanEdgeGatewaySchedulerAlarmCompositionMCamLimitsReachedOffMonitors 2 }

titanEdgeGatewaySchedulerAlarmCompositionMCamLimitsReachedOffName OBJECT-TYPE
    SYNTAX DisplayString
    MAX-ACCESS read-only
    STATUS current
    DESCRIPTION "."
    ::= { titanEdgeGatewaySchedulerAlarmCompositionMCamLimitsReachedOffMonitors 2 }

titanEdgeGatewaySchedulerAlarmCompositionMCamHardwareErrorOnNotification NOTIFICATION-TYPE
    OBJECTS {
        titanEdgeGatewaySchedulerAlarmCompositionMCamHardwareErrorOnId,
        titanEdgeGatewaySchedulerAlarmCompositionMCamHardwareErrorOnIndex
    }
    STATUS current
    DESCRIPTION "M-CAM pin hardware capacity is full"
    ::= { titanEdgeGatewaySchedulerAlarmCompositionMCamHardwareErrorOn 1 }

titanEdgeGatewaySchedulerAlarmCompositionMCamHardwareErrorOnId OBJECT-TYPE
    SYNTAX DisplayString
    MAX-ACCESS read-only
    STATUS current
    DESCRIPTION "."
    ::= { titanEdgeGatewaySchedulerAlarmCompositionMCamHardwareErrorOn 1 2 }

titanEdgeGatewaySchedulerAlarmCompositionMCamHardwareErrorOnIndex OBJECT-TYPE
    SYNTAX DisplayString
    MAX-ACCESS read-only
    STATUS current
    DESCRIPTION "."
    ::= { titanEdgeGatewaySchedulerAlarmCompositionMCamHardwareErrorOn 1 2 }

titanEdgeGatewaySchedulerAlarmCompositionMCamHardwareErrorOffNotification NOTIFICATION-TYPE
    OBJECTS {
        titanEdgeGatewaySchedulerAlarmCompositionMCamHardwareErrorOffId,
        titanEdgeGatewaySchedulerAlarmCompositionMCamHardwareErrorOffIndex
    }
    STATUS current
    DESCRIPTION "M-CAM pin hardware capacity is full"
    ::= { titanEdgeGatewaySchedulerAlarmCompositionMCamHardwareErrorOn 2 }

titanEdgeGatewaySchedulerAlarmCompositionMCamHardwareErrorOffId OBJECT-TYPE
    SYNTAX DisplayString
    MAX-ACCESS read-only
    STATUS current
    DESCRIPTION "."
    ::= { titanEdgeGatewaySchedulerAlarmCompositionMCamHardwareErrorOffMonitors 2 }

titanEdgeGatewaySchedulerAlarmCompositionMCamHardwareErrorOffIndex OBJECT-TYPE
    SYNTAX DisplayString
    MAX-ACCESS read-only
    STATUS current
    DESCRIPTION "."
    ::= { titanEdgeGatewaySchedulerAlarmCompositionMCamHardwareErrorOffMonitors 2 }

titanEdgeGatewaySchedulerAlarmOutputBitrateInvalidOnNotification NOTIFICATION-TYPE
    OBJECTS {
        titanEdgeGatewaySchedulerAlarmOutputBitrateInvalidOnId,
        titanEdgeGatewaySchedulerAlarmOutputBitrateInvalidOnIndex
    }
    STATUS current
    DESCRIPTION "Bitrate is invalid for output"
    ::= { titanEdgeGatewaySchedulerAlarmOutputBitrateInvalidOn 1 }

titanEdgeGatewaySchedulerAlarmOutputBitrateInvalidOnId OBJECT-TYPE
    SYNTAX DisplayString
    MAX-ACCESS read-only
    STATUS current
    DESCRIPTION "."
    ::= { titanEdgeGatewaySchedulerAlarmOutputBitrateInvalidOn 1 2 }

titanEdgeGatewaySchedulerAlarmOutputBitrateInvalidOnIndex OBJECT-TYPE
    SYNTAX DisplayString
    MAX-ACCESS read-only
    STATUS current
    DESCRIPTION "."
    ::= { titanEdgeGatewaySchedulerAlarmOutputBitrateInvalidOn 1 2 }

titanEdgeGatewaySchedulerAlarmOutputBitrateInvalidOffNotification NOTIFICATION-TYPE
    OBJECTS {
        titanEdgeGatewaySchedulerAlarmOutputBitrateInvalidOffId,
        titanEdgeGatewaySchedulerAlarmOutputBitrateInvalidOffIndex
    }
    STATUS current
    DESCRIPTION "Bitrate is invalid for output"
    ::= { titanEdgeGatewaySchedulerAlarmOutputBitrateInvalidOn 2 }

titanEdgeGatewaySchedulerAlarmOutputBitrateInvalidOffId OBJECT-TYPE
    SYNTAX DisplayString
    MAX-ACCESS read-only
    STATUS current
    DESCRIPTION "."
    ::= { titanEdgeGatewaySchedulerAlarmOutputBitrateInvalidOffMonitors 2 }

titanEdgeGatewaySchedulerAlarmOutputBitrateInvalidOffIndex OBJECT-TYPE
    SYNTAX DisplayString
    MAX-ACCESS read-only
    STATUS current
    DESCRIPTION "."
    ::= { titanEdgeGatewaySchedulerAlarmOutputBitrateInvalidOffMonitors 2 }

titanEdgeGatewaySchedulerAlarmCompositionMCamDuplicatedProgramsOnNotification NOTIFICATION-TYPE
    OBJECTS {
        titanEdgeGatewaySchedulerAlarmCompositionMCamDuplicatedProgramsOnId,
        titanEdgeGatewaySchedulerAlarmCompositionMCamDuplicatedProgramsOnIndex,
        titanEdgeGatewaySchedulerAlarmCompositionMCamDuplicatedProgramsOnName
    }
    STATUS current
    DESCRIPTION "Duplicated programs detected on the M-CAM pin"
    ::= { titanEdgeGatewaySchedulerAlarmCompositionMCamDuplicatedProgramsOn 1 }

titanEdgeGatewaySchedulerAlarmCompositionMCamDuplicatedProgramsOnId OBJECT-TYPE
    SYNTAX DisplayString
    MAX-ACCESS read-only
    STATUS current
    DESCRIPTION "."
    ::= { titanEdgeGatewaySchedulerAlarmCompositionMCamDuplicatedProgramsOn 1 2 }

titanEdgeGatewaySchedulerAlarmCompositionMCamDuplicatedProgramsOnIndex OBJECT-TYPE
    SYNTAX DisplayString
    MAX-ACCESS read-only
    STATUS current
    DESCRIPTION "."
    ::= { titanEdgeGatewaySchedulerAlarmCompositionMCamDuplicatedProgramsOn 1 2 }

titanEdgeGatewaySchedulerAlarmCompositionMCamDuplicatedProgramsOnName OBJECT-TYPE
    SYNTAX DisplayString
    MAX-ACCESS read-only
    STATUS current
    DESCRIPTION "."
    ::= { titanEdgeGatewaySchedulerAlarmCompositionMCamDuplicatedProgramsOn 1 2 }

titanEdgeGatewaySchedulerAlarmCompositionMCamDuplicatedProgramsOffNotification NOTIFICATION-TYPE
    OBJECTS {
        titanEdgeGatewaySchedulerAlarmCompositionMCamDuplicatedProgramsOffId,
        titanEdgeGatewaySchedulerAlarmCompositionMCamDuplicatedProgramsOffIndex,
        titanEdgeGatewaySchedulerAlarmCompositionMCamDuplicatedProgramsOffName
    }
    STATUS current
    DESCRIPTION "Duplicated programs detected on the M-CAM pin"
    ::= { titanEdgeGatewaySchedulerAlarmCompositionMCamDuplicatedProgramsOn 2 }

titanEdgeGatewaySchedulerAlarmCompositionMCamDuplicatedProgramsOffId OBJECT-TYPE
    SYNTAX DisplayString
    MAX-ACCESS read-only
    STATUS current
    DESCRIPTION "."
    ::= { titanEdgeGatewaySchedulerAlarmCompositionMCamDuplicatedProgramsOffMonitors 2 }

titanEdgeGatewaySchedulerAlarmCompositionMCamDuplicatedProgramsOffIndex OBJECT-TYPE
    SYNTAX DisplayString
    MAX-ACCESS read-only
    STATUS current
    DESCRIPTION "."
    ::= { titanEdgeGatewaySchedulerAlarmCompositionMCamDuplicatedProgramsOffMonitors 2 }

titanEdgeGatewaySchedulerAlarmCompositionMCamDuplicatedProgramsOffName OBJECT-TYPE
    SYNTAX DisplayString
    MAX-ACCESS read-only
    STATUS current
    DESCRIPTION "."
    ::= { titanEdgeGatewaySchedulerAlarmCompositionMCamDuplicatedProgramsOffMonitors 2 }

titanEdgeGatewayProcessingLogProcessingFailureNotification NOTIFICATION-TYPE
    OBJECTS {
        titanEdgeGatewayProcessingLogProcessingFailureId
    }
    STATUS current
    DESCRIPTION "Processing failure"
    ::= { titanEdgeGatewayProcessingLogs 9 }

titanEdgeGatewayProcessingLogProcessingFailureId OBJECT-TYPE
    SYNTAX DisplayString
    MAX-ACCESS read-only
    STATUS current
    DESCRIPTION "."
    ::= { titanEdgeGatewayProcessingLogs 9 2 }

END
