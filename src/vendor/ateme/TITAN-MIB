--
-- TITAN-MIB.mib
-- MIB generated by MG-SOFT Visual MIB Builder Version 6.0  Build 88
-- Tuesday, June 27, 2017 at 15:18:42
--

--  TITAN-MIB.mib
-- MIB generated by MG-SOFT Visual MIB Builder Version 6.0  Build 88
-- Wednesday, December 16, 2015 at 11:49:27
--

	TITAN-MIB DEFINITIONS ::= BEGIN

		IMPORTS
			OBJECT-GROUP, NOTIFICATION-GROUP
				FROM SNMPv2-CONF
			enterprises, OBJECT-TYPE, MODULE-IDENTITY, NOTIFICATION-TYPE
				FROM SNMPv2-SMI
			DateAndTime
				FROM SNMPv2-TC;		-- [RFC2579]


--  September 28, 2015 at 18:32 GMT
-- 1.3.6.1.4.1.27338
-- September 28, 2015 at 18:32 GMT
		-- 1.3.6.1.4.1.27338
		ateme MODULE-IDENTITY
			LAST-UPDATED "201905151645Z"		-- May 15, 2019 at 16:45 GMT
			ORGANIZATION
				"ATEME"
			CONTACT-INFO
				"products@ateme.com"
			DESCRIPTION
				"This module describes ATEME TITAN Live MIB."
			REVISION    "201905151645Z"		    -- May 15, 2019 at 16:45 GMT
			DESCRIPTION
				"Updated version, adds alarmSystemTime trap."

			::= { enterprises 27338 }



--
-- Node definitions
--

-- 1.3.6.1.4.1.27338.1
		-- 1.3.6.1.4.1.27338.1
		oids OBJECT IDENTIFIER ::= { ateme 1 }

		titanlive OBJECT IDENTIFIER ::= { oids 1 }

--    Node definitions
--
-- 1.3.6.1.4.1.27338.40
		-- 1.3.6.1.4.1.27338.40
		titan OBJECT IDENTIFIER ::= { ateme 40 }


--  1.3.6.1.4.1.27338.40.1
		-- 1.3.6.1.4.1.27338.40.1
		mibVersion OBJECT-TYPE
			SYNTAX OCTET STRING
			MAX-ACCESS read-only
			STATUS current
			DESCRIPTION
				"MIB version"
			::= { titan 1 }


--  1.3.6.1.4.1.27338.40.2
		-- 1.3.6.1.4.1.27338.40.2
		productName OBJECT-TYPE
			SYNTAX OCTET STRING
			MAX-ACCESS read-only
			STATUS current
			DESCRIPTION
				"Titan Live 4.0"
			::= { titan 2 }


--  1.3.6.1.4.1.27338.40.3
		-- 1.3.6.1.4.1.27338.40.3
		titanLiveInfoGroup OBJECT-GROUP
			OBJECTS { mibVersion, productName }
			STATUS current
			DESCRIPTION
				"Objects providing general information"
			::= { titan 3 }


--  1.3.6.1.4.1.27338.40.5
		-- 1.3.6.1.4.1.27338.40.5
		traps OBJECT IDENTIFIER ::= { titan 5 }


--  1.3.6.1.4.1.27338.40.5.1
		-- 1.3.6.1.4.1.27338.40.5.1
		alarmData OBJECT-GROUP
			OBJECTS { alarmName, alarmLevel, alarmDescription, alarmType, alarmStatus,
				alarmUID, alarmIpAddress, alarmServiceName, alarmSystemTime }
			STATUS current
			DESCRIPTION
				"Description."
			::= { traps 1 }


--  1.3.6.1.4.1.27338.40.5.2
		-- 1.3.6.1.4.1.27338.40.5.2
		trapsGroup NOTIFICATION-GROUP
			NOTIFICATIONS { alarm }
			STATUS current
			DESCRIPTION
				"TitanLive traps group"
			::= { traps 2 }


--  1.3.6.1.4.1.27338.40.5.3
		-- 1.3.6.1.4.1.27338.40.5.3
		alarm NOTIFICATION-TYPE
			OBJECTS { alarmName, alarmLevel, alarmDescription, alarmType, alarmStatus,
				alarmUID, alarmIpAddress, alarmServiceName, alarmSystemTime }
			STATUS current
			DESCRIPTION
				"TitanLive alarm"
			::= { traps 3 }


--  1.3.6.1.4.1.27338.40.5.4
		-- 1.3.6.1.4.1.27338.40.5.4
		alarmName OBJECT-TYPE
			SYNTAX OCTET STRING
			MAX-ACCESS read-write
			STATUS current
			DESCRIPTION
				"TITAN Live alarm name"
			::= { traps 4 }


--  1.3.6.1.4.1.27338.40.5.5
		-- 1.3.6.1.4.1.27338.40.5.5
		alarmDescription OBJECT-TYPE
			SYNTAX OCTET STRING
			MAX-ACCESS read-only
			STATUS current
			DESCRIPTION
				"Alarm description"
			::= { traps 5 }


--  1.3.6.1.4.1.27338.40.5.6
		-- 1.3.6.1.4.1.27338.40.5.6
		alarmType OBJECT-TYPE
			SYNTAX OCTET STRING
			MAX-ACCESS read-only
			STATUS current
			DESCRIPTION
				"Logs or transitory"
			::= { traps 6 }


--  1.3.6.1.4.1.27338.40.5.7
		-- 1.3.6.1.4.1.27338.40.5.7
		alarmStatus OBJECT-TYPE
			SYNTAX OCTET STRING
			MAX-ACCESS read-only
			STATUS current
			DESCRIPTION
				"Start or end to indicate if its the beginning or the end of an event"
			::= { traps 7 }


--  1.3.6.1.4.1.27338.40.5.8
		-- 1.3.6.1.4.1.27338.40.5.8
		alarmUID OBJECT-TYPE
			SYNTAX OCTET STRING
			MAX-ACCESS read-only
			STATUS current
			DESCRIPTION
				"UID of the service"
			::= { traps 8 }


--  1.3.6.1.4.1.27338.40.5.9
		-- 1.3.6.1.4.1.27338.40.5.9
		alarmLevel OBJECT-TYPE
			SYNTAX OCTET STRING
			MAX-ACCESS read-only
			STATUS current
			DESCRIPTION
				"Criticity of the alarm"
			::= { traps 9 }


		-- 1.3.6.1.4.1.27338.40.5.10
		alarmIpAddress OBJECT-TYPE
			SYNTAX OCTET STRING
			MAX-ACCESS read-only
			STATUS current
			DESCRIPTION
				"Description."
			::= { traps 10 }


		-- 1.3.6.1.4.1.27338.40.5.11
		alarmServiceName OBJECT-TYPE
			SYNTAX OCTET STRING
			MAX-ACCESS read-only
			STATUS current
			DESCRIPTION
				"Name of the service."
			::= { traps 11 }


		-- 1.3.6.1.4.1.27338.40.5.12
		alarmSystemTime OBJECT-TYPE
			SYNTAX DateAndTime
			MAX-ACCESS read-only
			STATUS current
			DESCRIPTION
				"System date and time."
			::= { traps 12 }


	END

--
-- TITAN-MIB.mib
--
