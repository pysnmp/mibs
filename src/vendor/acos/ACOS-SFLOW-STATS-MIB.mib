ACOS-SFLOW-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosSflow MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Sflow OID for ACOS"
				::=  {  acosRootStats 125  }

acosSflowGlobal                     OBJECT IDENTIFIER ::= { acosSflow 7 }
acosSflowGlobalS                    OBJECT IDENTIFIER ::= { acosSflowGlobal 1 }

		totalPacketSampleRecords OBJECT-TYPE
		SYNTAX  CounterBasedGauge64 
		MAX-ACCESS read-only 
		STATUS current
		DESCRIPTION  "Total packet sample records" 
		::={ acosSflowGlobalS 1 } 

		totalCounterSampleRecords OBJECT-TYPE
		SYNTAX  CounterBasedGauge64 
		MAX-ACCESS read-only 
		STATUS current
		DESCRIPTION  "Total counter sample records" 
		::={ acosSflowGlobalS 2 } 

		totalSflowPacketsSent OBJECT-TYPE
		SYNTAX  CounterBasedGauge64 
		MAX-ACCESS read-only 
		STATUS current
		DESCRIPTION  "Total sflow packets sent" 
		::={ acosSflowGlobalS 3 } 

		totalSflowLocalPacketsSent OBJECT-TYPE
		SYNTAX  CounterBasedGauge64 
		MAX-ACCESS read-only 
		STATUS current
		DESCRIPTION  "Total sflow packets sent  desc {}" 
		::={ acosSflowGlobalS 4 } 

		totalSflowPacketsSentMgmt OBJECT-TYPE
		SYNTAX  CounterBasedGauge64 
		MAX-ACCESS read-only 
		STATUS current
		DESCRIPTION  "Total sflow packets sent via Mgmt Interface" 
		::={ acosSflowGlobalS 5 } 

		totalSflowPacketsDropMgmt OBJECT-TYPE
		SYNTAX  CounterBasedGauge64 
		MAX-ACCESS read-only 
		STATUS current
		DESCRIPTION  "sflow packets dropped because of rate limit via Mgmt Interface" 
		::={ acosSflowGlobalS 6 } 

END
