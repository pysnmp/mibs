ACOS-FW-OPER-MIB DEFINITIONS ::= BEGIN
	IMPORTS
		DisplayString, PhysAddress
		FROM SNMPv2-TC
	InetAddressType
		FROM INET-ADDRESS-MIB
	acosRootOper
		FROM A10-AX-MIB
	MODULE-IDENTITY, OBJECT-TYPE, Counter32, Integer32, Counter64, OBJECT-IDENTITY, NOTIFICATION-TYPE
		FROM SNMPv2-SMI;
		acosFw MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Fw OID for ACOS"
				::=  {  acosRootOper 139  }

acosFwLimitEntry                    OBJECT IDENTIFIER ::= { acosFw 20 }

fwLimitEntryLimitEntryTable OBJECT-TYPE
		SYNTAX SEQUENCE OF FwLimitEntryLimitEntryEntry
		MAX-ACCESS not-accessible
		STATUS current
		::={ acosFwLimitEntry 1 } 


	fwLimitEntryLimitEntryEntry OBJECT-TYPE
		SYNTAX FwLimitEntryLimitEntryEntry
		MAX-ACCESS not-accessible
		STATUS current
		INDEX {
			address,
			prefixLen,
			ruleName
		}
		::={ fwLimitEntryLimitEntryTable 1 } 


	FwLimitEntryLimitEntryEntry ::=
		SEQUENCE {
			address DisplayString, 
			prefixLen INTEGER, 
			ruleName DisplayString, 
			stringValue DisplayString,
			currCount CounterBasedGauge64,
			maxCount CounterBasedGauge64,
			type DisplayString
		}

		address OBJECT-TYPE
		SYNTAX  DisplayString 
		MAX-ACCESS read-only 
		STATUS current
		DESCRIPTION  "" 
		::={ fwLimitEntryLimitEntryEntry 1 } 

		prefixLen OBJECT-TYPE
		SYNTAX  INTEGER 
		MAX-ACCESS read-only 
		STATUS current
		DESCRIPTION  "" 
		::={ fwLimitEntryLimitEntryEntry 2 } 

		stringValue OBJECT-TYPE
		SYNTAX  DisplayString 
		MAX-ACCESS read-only 
		STATUS current
		DESCRIPTION  "" 
		::={ fwLimitEntryLimitEntryEntry 3 } 

		ruleName OBJECT-TYPE
		SYNTAX  DisplayString 
		MAX-ACCESS read-only 
		STATUS current
		DESCRIPTION  "" 
		::={ fwLimitEntryLimitEntryEntry 4 } 

		currCount OBJECT-TYPE
		SYNTAX  CounterBasedGauge64 
		MAX-ACCESS read-only 
		STATUS current
		DESCRIPTION  "" 
		::={ fwLimitEntryLimitEntryEntry 5 } 

		maxCount OBJECT-TYPE
		SYNTAX  CounterBasedGauge64 
		MAX-ACCESS read-only 
		STATUS current
		DESCRIPTION  "" 
		::={ fwLimitEntryLimitEntryEntry 6 } 

		type OBJECT-TYPE
		SYNTAX  DisplayString 
		MAX-ACCESS read-only 
		STATUS current
		DESCRIPTION  "" 
		::={ fwLimitEntryLimitEntryEntry 7 } 

acosFwRateLimit                     OBJECT IDENTIFIER ::= { acosFw 30 }

fwRateLimitRateLimitTable OBJECT-TYPE
		SYNTAX SEQUENCE OF FwRateLimitRateLimitEntry
		MAX-ACCESS not-accessible
		STATUS current
		::={ acosFwRateLimit 1 } 


	fwRateLimitRateLimitEntry OBJECT-TYPE
		SYNTAX FwRateLimitRateLimitEntry
		MAX-ACCESS not-accessible
		STATUS current
		INDEX {
			stringValue,
			address,
			ruleName
		}
		::={ fwRateLimitRateLimitTable 1 } 


	FwRateLimitRateLimitEntry ::=
		SEQUENCE {
			stringValue DisplayString, 
			address DisplayString, 
			ruleName DisplayString, 
			prefixLen CounterBasedGauge64,
			templateId CounterBasedGauge64,
			type DisplayString,
			cpsReceived CounterBasedGauge64,
			cpsAllowed CounterBasedGauge64,
			uplinkTrafficReceived CounterBasedGauge64,
			uplinkTrafficAllowed CounterBasedGauge64,
			downlinkTrafficReceived CounterBasedGauge64,
			downlinkTrafficAllowed CounterBasedGauge64,
			totalTrafficReceived CounterBasedGauge64,
			totalTrafficAllowed CounterBasedGauge64,
			dropCount CounterBasedGauge64
		}

		stringValue OBJECT-TYPE
		SYNTAX  DisplayString 
		MAX-ACCESS read-only 
		STATUS current
		DESCRIPTION  "" 
		::={ fwRateLimitRateLimitEntry 1 } 

		address OBJECT-TYPE
		SYNTAX  DisplayString 
		MAX-ACCESS read-only 
		STATUS current
		DESCRIPTION  "" 
		::={ fwRateLimitRateLimitEntry 2 } 

		prefixLen OBJECT-TYPE
		SYNTAX  INTEGER 
		MAX-ACCESS read-only 
		STATUS current
		DESCRIPTION  "" 
		::={ fwRateLimitRateLimitEntry 3 } 

		ruleName OBJECT-TYPE
		SYNTAX  DisplayString 
		MAX-ACCESS read-only 
		STATUS current
		DESCRIPTION  "" 
		::={ fwRateLimitRateLimitEntry 4 } 

		templateId OBJECT-TYPE
		SYNTAX  CounterBasedGauge64 
		MAX-ACCESS read-only 
		STATUS current
		DESCRIPTION  "" 
		::={ fwRateLimitRateLimitEntry 5 } 

		type OBJECT-TYPE
		SYNTAX  DisplayString 
		MAX-ACCESS read-only 
		STATUS current
		DESCRIPTION  "" 
		::={ fwRateLimitRateLimitEntry 6 } 

		cpsReceived OBJECT-TYPE
		SYNTAX  CounterBasedGauge64 
		MAX-ACCESS read-only 
		STATUS current
		DESCRIPTION  "" 
		::={ fwRateLimitRateLimitEntry 7 } 

		cpsAllowed OBJECT-TYPE
		SYNTAX  CounterBasedGauge64 
		MAX-ACCESS read-only 
		STATUS current
		DESCRIPTION  "" 
		::={ fwRateLimitRateLimitEntry 8 } 

		uplinkTrafficReceived OBJECT-TYPE
		SYNTAX  CounterBasedGauge64 
		MAX-ACCESS read-only 
		STATUS current
		DESCRIPTION  "" 
		::={ fwRateLimitRateLimitEntry 9 } 

		uplinkTrafficAllowed OBJECT-TYPE
		SYNTAX  CounterBasedGauge64 
		MAX-ACCESS read-only 
		STATUS current
		DESCRIPTION  "" 
		::={ fwRateLimitRateLimitEntry 10 } 

		downlinkTrafficReceived OBJECT-TYPE
		SYNTAX  CounterBasedGauge64 
		MAX-ACCESS read-only 
		STATUS current
		DESCRIPTION  "" 
		::={ fwRateLimitRateLimitEntry 11 } 

		downlinkTrafficAllowed OBJECT-TYPE
		SYNTAX  CounterBasedGauge64 
		MAX-ACCESS read-only 
		STATUS current
		DESCRIPTION  "" 
		::={ fwRateLimitRateLimitEntry 12 } 

		totalTrafficReceived OBJECT-TYPE
		SYNTAX  CounterBasedGauge64 
		MAX-ACCESS read-only 
		STATUS current
		DESCRIPTION  "" 
		::={ fwRateLimitRateLimitEntry 13 } 

		totalTrafficAllowed OBJECT-TYPE
		SYNTAX  CounterBasedGauge64 
		MAX-ACCESS read-only 
		STATUS current
		DESCRIPTION  "" 
		::={ fwRateLimitRateLimitEntry 14 } 

		dropCount OBJECT-TYPE
		SYNTAX  CounterBasedGauge64 
		MAX-ACCESS read-only 
		STATUS current
		DESCRIPTION  "" 
		::={ fwRateLimitRateLimitEntry 15 } 

acosFwRateLimitSummary              OBJECT IDENTIFIER ::= { acosFwRateLimit 1 }

		memReserved OBJECT-TYPE
		SYNTAX  CounterBasedGauge64 
		MAX-ACCESS read-only 
		STATUS current
		DESCRIPTION  "" 
		::={ acosFwRateLimitSummary 1 } 

		memUsed OBJECT-TYPE
		SYNTAX  CounterBasedGauge64 
		MAX-ACCESS read-only 
		STATUS current
		DESCRIPTION  "" 
		::={ acosFwRateLimitSummary 2 } 

		allocFailures OBJECT-TYPE
		SYNTAX  CounterBasedGauge64 
		MAX-ACCESS read-only 
		STATUS current
		DESCRIPTION  "" 
		::={ acosFwRateLimitSummary 3 } 

		totalNumEntries OBJECT-TYPE
		SYNTAX  CounterBasedGauge64 
		MAX-ACCESS read-only 
		STATUS current
		DESCRIPTION  "" 
		::={ acosFwRateLimitSummary 4 } 

		totalNumEntriesAllocated OBJECT-TYPE
		SYNTAX  CounterBasedGauge64 
		MAX-ACCESS read-only 
		STATUS current
		DESCRIPTION  "" 
		::={ acosFwRateLimitSummary 5 } 

		totalNumEntriesFreed OBJECT-TYPE
		SYNTAX  CounterBasedGauge64 
		MAX-ACCESS read-only 
		STATUS current
		DESCRIPTION  "" 
		::={ acosFwRateLimitSummary 6 } 

		totalEntriesScopeAggregate OBJECT-TYPE
		SYNTAX  CounterBasedGauge64 
		MAX-ACCESS read-only 
		STATUS current
		DESCRIPTION  "" 
		::={ acosFwRateLimitSummary 7 } 

		totalEntriesScopeSubscriberIp OBJECT-TYPE
		SYNTAX  CounterBasedGauge64 
		MAX-ACCESS read-only 
		STATUS current
		DESCRIPTION  "" 
		::={ acosFwRateLimitSummary 8 } 

		totalEntriesScopeSubscriberPrefix OBJECT-TYPE
		SYNTAX  CounterBasedGauge64 
		MAX-ACCESS read-only 
		STATUS current
		DESCRIPTION  "" 
		::={ acosFwRateLimitSummary 9 } 

		totalEntriesScopeRadiusUsergroup OBJECT-TYPE
		SYNTAX  CounterBasedGauge64 
		MAX-ACCESS read-only 
		STATUS current
		DESCRIPTION  "" 
		::={ acosFwRateLimitSummary 10 } 

		totalEntriesScopeRadiusUserid OBJECT-TYPE
		SYNTAX  CounterBasedGauge64 
		MAX-ACCESS read-only 
		STATUS current
		DESCRIPTION  "" 
		::={ acosFwRateLimitSummary 11 } 

		totalEntriesScopeParent OBJECT-TYPE
		SYNTAX  CounterBasedGauge64 
		MAX-ACCESS read-only 
		STATUS current
		DESCRIPTION  "" 
		::={ acosFwRateLimitSummary 12 } 

		totalEntriesScopeParentSubscriberIp OBJECT-TYPE
		SYNTAX  CounterBasedGauge64 
		MAX-ACCESS read-only 
		STATUS current
		DESCRIPTION  "" 
		::={ acosFwRateLimitSummary 13 } 

		totalEntriesScopeParentSubscriberPrefix OBJECT-TYPE
		SYNTAX  CounterBasedGauge64 
		MAX-ACCESS read-only 
		STATUS current
		DESCRIPTION  "" 
		::={ acosFwRateLimitSummary 14 } 

		totalEntriesScopeParentRadiusUsergroup OBJECT-TYPE
		SYNTAX  CounterBasedGauge64 
		MAX-ACCESS read-only 
		STATUS current
		DESCRIPTION  "" 
		::={ acosFwRateLimitSummary 15 } 

		totalEntriesScopeParentRadiusUserid OBJECT-TYPE
		SYNTAX  CounterBasedGauge64 
		MAX-ACCESS read-only 
		STATUS current
		DESCRIPTION  "" 
		::={ acosFwRateLimitSummary 16 } 

acosFwFullConeSession               OBJECT IDENTIFIER ::= { acosFw 16 }

fwFullConeSessionSessionTable OBJECT-TYPE
		SYNTAX SEQUENCE OF FwFullConeSessionSessionEntry
		MAX-ACCESS not-accessible
		STATUS current
		::={ acosFwFullConeSession 1 } 


	fwFullConeSessionSessionEntry OBJECT-TYPE
		SYNTAX FwFullConeSessionSessionEntry
		MAX-ACCESS not-accessible
		STATUS current
		INDEX {
			protocol,
			insideAddress,
			insidePort
		}
		::={ fwFullConeSessionSessionTable 1 } 


	FwFullConeSessionSessionEntry ::=
		SEQUENCE {
			protocol DisplayString, 
			insideAddress DisplayString, 
			insidePort INTEGER, 
			outbound CounterBasedGauge64,
			inbound CounterBasedGauge64,
			cpu CounterBasedGauge64,
			age DisplayString
		}

		protocol OBJECT-TYPE
		SYNTAX  DisplayString 
		MAX-ACCESS read-only 
		STATUS current
		DESCRIPTION  "" 
		::={ fwFullConeSessionSessionEntry 1 } 

		insideAddress OBJECT-TYPE
		SYNTAX  DisplayString 
		MAX-ACCESS read-only 
		STATUS current
		DESCRIPTION  "" 
		::={ fwFullConeSessionSessionEntry 2 } 

		insidePort OBJECT-TYPE
		SYNTAX  INTEGER 
		MAX-ACCESS read-only 
		STATUS current
		DESCRIPTION  "" 
		::={ fwFullConeSessionSessionEntry 3 } 

		outbound OBJECT-TYPE
		SYNTAX  CounterBasedGauge64 
		MAX-ACCESS read-only 
		STATUS current
		DESCRIPTION  "" 
		::={ fwFullConeSessionSessionEntry 4 } 

		inbound OBJECT-TYPE
		SYNTAX  CounterBasedGauge64 
		MAX-ACCESS read-only 
		STATUS current
		DESCRIPTION  "" 
		::={ fwFullConeSessionSessionEntry 5 } 

		cpu OBJECT-TYPE
		SYNTAX  CounterBasedGauge64 
		MAX-ACCESS read-only 
		STATUS current
		DESCRIPTION  "" 
		::={ fwFullConeSessionSessionEntry 6 } 

		age OBJECT-TYPE
		SYNTAX  DisplayString 
		MAX-ACCESS read-only 
		STATUS current
		DESCRIPTION  "" 
		::={ fwFullConeSessionSessionEntry 7 } 

acosFwSystemStatus                  OBJECT IDENTIFIER ::= { acosFw 18 }

		dataSessionsUsed OBJECT-TYPE
		SYNTAX  CounterBasedGauge64 
		MAX-ACCESS read-only 
		STATUS current
		DESCRIPTION  "" 
		::={ acosFwSystemStatus 1 } 

		dataSessionsFree OBJECT-TYPE
		SYNTAX  CounterBasedGauge64 
		MAX-ACCESS read-only 
		STATUS current
		DESCRIPTION  "" 
		::={ acosFwSystemStatus 2 } 

		smpSessionsUsed OBJECT-TYPE
		SYNTAX  CounterBasedGauge64 
		MAX-ACCESS read-only 
		STATUS current
		DESCRIPTION  "" 
		::={ acosFwSystemStatus 3 } 

		smpSessionsFree OBJECT-TYPE
		SYNTAX  CounterBasedGauge64 
		MAX-ACCESS read-only 
		STATUS current
		DESCRIPTION  "" 
		::={ acosFwSystemStatus 4 } 

		radiusEntriesUsed OBJECT-TYPE
		SYNTAX  CounterBasedGauge64 
		MAX-ACCESS read-only 
		STATUS current
		DESCRIPTION  "" 
		::={ acosFwSystemStatus 5 } 

		radiusEntriesFree OBJECT-TYPE
		SYNTAX  CounterBasedGauge64 
		MAX-ACCESS read-only 
		STATUS current
		DESCRIPTION  "" 
		::={ acosFwSystemStatus 6 } 

END
