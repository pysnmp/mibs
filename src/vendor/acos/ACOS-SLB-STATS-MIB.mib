ACOS-SLB-STATS-MIB DEFINITIONS ::= BEGIN
	IMPORTS
		DisplayString, PhysAddress
		FROM SNMPv2-TC
	InetAddressType
		FROM INET-ADDRESS-MIB
	acosRootStats
		FROM A10-AX-MIB
	MODULE-IDENTITY, OBJECT-TYPE, Counter32, Integer32, Counter64, OBJECT-IDENTITY, NOTIFICATION-TYPE
		FROM SNMPv2-SMI;
		acosSlb MODULE-IDENTITY
				LAST-UPDATED	"200705071327Z"
				ORGANIZATION	"A10 Networks, Inc."
				CONTACT-INFO	"Address: A10 Networks, Inc.
							  3 West Pumeria Dr.
							  San Jose, CA 95131
						 Phone:   +1-888-822-7210 (USA/Canada)
						          +1-408-325-8676 (International)
						 E-mail:  support@A10Networks.com"

				DESCRIPTION	 "Slb OID for ACOS"
				::=  {  acosRootStats 108  }

acosSlbSslError                     OBJECT IDENTIFIER ::= { acosSlb 62 }
acosSlbSslErrorS                    OBJECT IDENTIFIER ::= { acosSlbSslError 1 }

		appDataInHandshake OBJECT-TYPE
		SYNTAX  CounterBasedGauge64 
		MAX-ACCESS read-only 
		STATUS current
		DESCRIPTION  "app data in handshake" 
		::={ acosSlbSslErrorS 1 } 

		attemptToReuseSessInDiffContext OBJECT-TYPE
		SYNTAX  CounterBasedGauge64 
		MAX-ACCESS read-only 
		STATUS current
		DESCRIPTION  "attempt to reuse sess in diff context" 
		::={ acosSlbSslErrorS 2 } 

		badAlertRecord OBJECT-TYPE
		SYNTAX  CounterBasedGauge64 
		MAX-ACCESS read-only 
		STATUS current
		DESCRIPTION  "bad alert record" 
		::={ acosSlbSslErrorS 3 } 

		badAuthenticationType OBJECT-TYPE
		SYNTAX  CounterBasedGauge64 
		MAX-ACCESS read-only 
		STATUS current
		DESCRIPTION  "bad authentication type" 
		::={ acosSlbSslErrorS 4 } 

		badChangeCipherSpec OBJECT-TYPE
		SYNTAX  CounterBasedGauge64 
		MAX-ACCESS read-only 
		STATUS current
		DESCRIPTION  "bad change cipher spec" 
		::={ acosSlbSslErrorS 5 } 

		badChecksum OBJECT-TYPE
		SYNTAX  CounterBasedGauge64 
		MAX-ACCESS read-only 
		STATUS current
		DESCRIPTION  "bad checksum" 
		::={ acosSlbSslErrorS 6 } 

		badDataReturnedByCallback OBJECT-TYPE
		SYNTAX  CounterBasedGauge64 
		MAX-ACCESS read-only 
		STATUS current
		DESCRIPTION  "bad data returned by callback" 
		::={ acosSlbSslErrorS 7 } 

		badDecompression OBJECT-TYPE
		SYNTAX  CounterBasedGauge64 
		MAX-ACCESS read-only 
		STATUS current
		DESCRIPTION  "bad decompression" 
		::={ acosSlbSslErrorS 8 } 

		badDhGLength OBJECT-TYPE
		SYNTAX  CounterBasedGauge64 
		MAX-ACCESS read-only 
		STATUS current
		DESCRIPTION  "bad dh g length" 
		::={ acosSlbSslErrorS 9 } 

		badDhPubKeyLength OBJECT-TYPE
		SYNTAX  CounterBasedGauge64 
		MAX-ACCESS read-only 
		STATUS current
		DESCRIPTION  "bad dh pub key length" 
		::={ acosSlbSslErrorS 10 } 

		badDhPLength OBJECT-TYPE
		SYNTAX  CounterBasedGauge64 
		MAX-ACCESS read-only 
		STATUS current
		DESCRIPTION  "bad dh p length" 
		::={ acosSlbSslErrorS 11 } 

		badDigestLength OBJECT-TYPE
		SYNTAX  CounterBasedGauge64 
		MAX-ACCESS read-only 
		STATUS current
		DESCRIPTION  "bad digest length" 
		::={ acosSlbSslErrorS 12 } 

		badDsaSignature OBJECT-TYPE
		SYNTAX  CounterBasedGauge64 
		MAX-ACCESS read-only 
		STATUS current
		DESCRIPTION  "bad dsa signature" 
		::={ acosSlbSslErrorS 13 } 

		badHelloRequest OBJECT-TYPE
		SYNTAX  CounterBasedGauge64 
		MAX-ACCESS read-only 
		STATUS current
		DESCRIPTION  "bad hello request" 
		::={ acosSlbSslErrorS 14 } 

		badLength OBJECT-TYPE
		SYNTAX  CounterBasedGauge64 
		MAX-ACCESS read-only 
		STATUS current
		DESCRIPTION  "bad length" 
		::={ acosSlbSslErrorS 15 } 

		badMacDecode OBJECT-TYPE
		SYNTAX  CounterBasedGauge64 
		MAX-ACCESS read-only 
		STATUS current
		DESCRIPTION  "bad mac decode" 
		::={ acosSlbSslErrorS 16 } 

		badMessageType OBJECT-TYPE
		SYNTAX  CounterBasedGauge64 
		MAX-ACCESS read-only 
		STATUS current
		DESCRIPTION  "bad message type" 
		::={ acosSlbSslErrorS 17 } 

		badPacketLength OBJECT-TYPE
		SYNTAX  CounterBasedGauge64 
		MAX-ACCESS read-only 
		STATUS current
		DESCRIPTION  "bad packet length" 
		::={ acosSlbSslErrorS 18 } 

		badProtocolVersionCounter OBJECT-TYPE
		SYNTAX  CounterBasedGauge64 
		MAX-ACCESS read-only 
		STATUS current
		DESCRIPTION  "bad protocol version counter" 
		::={ acosSlbSslErrorS 19 } 

		badResponseArgument OBJECT-TYPE
		SYNTAX  CounterBasedGauge64 
		MAX-ACCESS read-only 
		STATUS current
		DESCRIPTION  "bad response argument" 
		::={ acosSlbSslErrorS 20 } 

		badRsaDecrypt OBJECT-TYPE
		SYNTAX  CounterBasedGauge64 
		MAX-ACCESS read-only 
		STATUS current
		DESCRIPTION  "bad rsa decrypt" 
		::={ acosSlbSslErrorS 21 } 

		badRsaEncrypt OBJECT-TYPE
		SYNTAX  CounterBasedGauge64 
		MAX-ACCESS read-only 
		STATUS current
		DESCRIPTION  "bad rsa encrypt" 
		::={ acosSlbSslErrorS 22 } 

		badRsaELength OBJECT-TYPE
		SYNTAX  CounterBasedGauge64 
		MAX-ACCESS read-only 
		STATUS current
		DESCRIPTION  "bad rsa e length" 
		::={ acosSlbSslErrorS 23 } 

		badRsaModulusLength OBJECT-TYPE
		SYNTAX  CounterBasedGauge64 
		MAX-ACCESS read-only 
		STATUS current
		DESCRIPTION  "bad rsa modulus length" 
		::={ acosSlbSslErrorS 24 } 

		badRsaSignature OBJECT-TYPE
		SYNTAX  CounterBasedGauge64 
		MAX-ACCESS read-only 
		STATUS current
		DESCRIPTION  "bad rsa signature" 
		::={ acosSlbSslErrorS 25 } 

		badSignature OBJECT-TYPE
		SYNTAX  CounterBasedGauge64 
		MAX-ACCESS read-only 
		STATUS current
		DESCRIPTION  "bad signature" 
		::={ acosSlbSslErrorS 26 } 

		badSslFiletype OBJECT-TYPE
		SYNTAX  CounterBasedGauge64 
		MAX-ACCESS read-only 
		STATUS current
		DESCRIPTION  "bad ssl filetype" 
		::={ acosSlbSslErrorS 27 } 

		badSslSessionIdLength OBJECT-TYPE
		SYNTAX  CounterBasedGauge64 
		MAX-ACCESS read-only 
		STATUS current
		DESCRIPTION  "bad ssl session id length" 
		::={ acosSlbSslErrorS 28 } 

		badState OBJECT-TYPE
		SYNTAX  CounterBasedGauge64 
		MAX-ACCESS read-only 
		STATUS current
		DESCRIPTION  "bad state" 
		::={ acosSlbSslErrorS 29 } 

		badWriteRetry OBJECT-TYPE
		SYNTAX  CounterBasedGauge64 
		MAX-ACCESS read-only 
		STATUS current
		DESCRIPTION  "bad write retry" 
		::={ acosSlbSslErrorS 30 } 

		bioNotSet OBJECT-TYPE
		SYNTAX  CounterBasedGauge64 
		MAX-ACCESS read-only 
		STATUS current
		DESCRIPTION  "bio not set" 
		::={ acosSlbSslErrorS 31 } 

		blockCipherPadIsWrong OBJECT-TYPE
		SYNTAX  CounterBasedGauge64 
		MAX-ACCESS read-only 
		STATUS current
		DESCRIPTION  "block cipher pad is wrong" 
		::={ acosSlbSslErrorS 32 } 

		bnLib OBJECT-TYPE
		SYNTAX  CounterBasedGauge64 
		MAX-ACCESS read-only 
		STATUS current
		DESCRIPTION  "bn lib" 
		::={ acosSlbSslErrorS 33 } 

		caDnLengthMismatch OBJECT-TYPE
		SYNTAX  CounterBasedGauge64 
		MAX-ACCESS read-only 
		STATUS current
		DESCRIPTION  "ca dn length mismatch" 
		::={ acosSlbSslErrorS 34 } 

		caDnTooLong OBJECT-TYPE
		SYNTAX  CounterBasedGauge64 
		MAX-ACCESS read-only 
		STATUS current
		DESCRIPTION  "ca dn too long" 
		::={ acosSlbSslErrorS 35 } 

		ccsReceivedEarly OBJECT-TYPE
		SYNTAX  CounterBasedGauge64 
		MAX-ACCESS read-only 
		STATUS current
		DESCRIPTION  "ccs received early" 
		::={ acosSlbSslErrorS 36 } 

		certificateVerifyFailed OBJECT-TYPE
		SYNTAX  CounterBasedGauge64 
		MAX-ACCESS read-only 
		STATUS current
		DESCRIPTION  "certificate verify failed" 
		::={ acosSlbSslErrorS 37 } 

		certLengthMismatch OBJECT-TYPE
		SYNTAX  CounterBasedGauge64 
		MAX-ACCESS read-only 
		STATUS current
		DESCRIPTION  "cert length mismatch" 
		::={ acosSlbSslErrorS 38 } 

		challengeIsDifferent OBJECT-TYPE
		SYNTAX  CounterBasedGauge64 
		MAX-ACCESS read-only 
		STATUS current
		DESCRIPTION  "challenge is different" 
		::={ acosSlbSslErrorS 39 } 

		cipherCodeWrongLength OBJECT-TYPE
		SYNTAX  CounterBasedGauge64 
		MAX-ACCESS read-only 
		STATUS current
		DESCRIPTION  "cipher code wrong length" 
		::={ acosSlbSslErrorS 40 } 

		cipherOrHashUnavailable OBJECT-TYPE
		SYNTAX  CounterBasedGauge64 
		MAX-ACCESS read-only 
		STATUS current
		DESCRIPTION  "cipher or hash unavailable" 
		::={ acosSlbSslErrorS 41 } 

		cipherTableSrcError OBJECT-TYPE
		SYNTAX  CounterBasedGauge64 
		MAX-ACCESS read-only 
		STATUS current
		DESCRIPTION  "cipher table src error" 
		::={ acosSlbSslErrorS 42 } 

		compressedLengthTooLong OBJECT-TYPE
		SYNTAX  CounterBasedGauge64 
		MAX-ACCESS read-only 
		STATUS current
		DESCRIPTION  "compressed length too long" 
		::={ acosSlbSslErrorS 43 } 

		compressionFailure OBJECT-TYPE
		SYNTAX  CounterBasedGauge64 
		MAX-ACCESS read-only 
		STATUS current
		DESCRIPTION  "compression failure" 
		::={ acosSlbSslErrorS 44 } 

		compressionLibraryError OBJECT-TYPE
		SYNTAX  CounterBasedGauge64 
		MAX-ACCESS read-only 
		STATUS current
		DESCRIPTION  "compression library error" 
		::={ acosSlbSslErrorS 45 } 

		connectionIdIsDifferent OBJECT-TYPE
		SYNTAX  CounterBasedGauge64 
		MAX-ACCESS read-only 
		STATUS current
		DESCRIPTION  "connection id is different" 
		::={ acosSlbSslErrorS 46 } 

		connectionTypeNotSet OBJECT-TYPE
		SYNTAX  CounterBasedGauge64 
		MAX-ACCESS read-only 
		STATUS current
		DESCRIPTION  "connection type not set" 
		::={ acosSlbSslErrorS 47 } 

		dataBetweenCcsAndFinished OBJECT-TYPE
		SYNTAX  CounterBasedGauge64 
		MAX-ACCESS read-only 
		STATUS current
		DESCRIPTION  "data between ccs and finished" 
		::={ acosSlbSslErrorS 48 } 

		dataLengthTooLong OBJECT-TYPE
		SYNTAX  CounterBasedGauge64 
		MAX-ACCESS read-only 
		STATUS current
		DESCRIPTION  "data length too long" 
		::={ acosSlbSslErrorS 49 } 

		decryptionFailed OBJECT-TYPE
		SYNTAX  CounterBasedGauge64 
		MAX-ACCESS read-only 
		STATUS current
		DESCRIPTION  "decryption failed" 
		::={ acosSlbSslErrorS 50 } 

		decryptionFailedOrBadRecordMac OBJECT-TYPE
		SYNTAX  CounterBasedGauge64 
		MAX-ACCESS read-only 
		STATUS current
		DESCRIPTION  "decryption failed or bad record mac" 
		::={ acosSlbSslErrorS 51 } 

		dhPublicValueLengthIsWrong OBJECT-TYPE
		SYNTAX  CounterBasedGauge64 
		MAX-ACCESS read-only 
		STATUS current
		DESCRIPTION  "dh public value length is wrong" 
		::={ acosSlbSslErrorS 52 } 

		digestCheckFailed OBJECT-TYPE
		SYNTAX  CounterBasedGauge64 
		MAX-ACCESS read-only 
		STATUS current
		DESCRIPTION  "digest check failed" 
		::={ acosSlbSslErrorS 53 } 

		encryptedLengthTooLong OBJECT-TYPE
		SYNTAX  CounterBasedGauge64 
		MAX-ACCESS read-only 
		STATUS current
		DESCRIPTION  "encrypted length too long" 
		::={ acosSlbSslErrorS 54 } 

		errorGeneratingTmpRsaKey OBJECT-TYPE
		SYNTAX  CounterBasedGauge64 
		MAX-ACCESS read-only 
		STATUS current
		DESCRIPTION  "error generating tmp rsa key" 
		::={ acosSlbSslErrorS 55 } 

		errorInReceivedCipherList OBJECT-TYPE
		SYNTAX  CounterBasedGauge64 
		MAX-ACCESS read-only 
		STATUS current
		DESCRIPTION  "error in received cipher list" 
		::={ acosSlbSslErrorS 56 } 

		excessiveMessageSize OBJECT-TYPE
		SYNTAX  CounterBasedGauge64 
		MAX-ACCESS read-only 
		STATUS current
		DESCRIPTION  "excessive message size" 
		::={ acosSlbSslErrorS 57 } 

		extraDataInMessage OBJECT-TYPE
		SYNTAX  CounterBasedGauge64 
		MAX-ACCESS read-only 
		STATUS current
		DESCRIPTION  "extra data in message" 
		::={ acosSlbSslErrorS 58 } 

		gotAFinBeforeACcs OBJECT-TYPE
		SYNTAX  CounterBasedGauge64 
		MAX-ACCESS read-only 
		STATUS current
		DESCRIPTION  "got a fin before a ccs" 
		::={ acosSlbSslErrorS 59 } 

		httpsProxyRequest OBJECT-TYPE
		SYNTAX  CounterBasedGauge64 
		MAX-ACCESS read-only 
		STATUS current
		DESCRIPTION  "https proxy request" 
		::={ acosSlbSslErrorS 60 } 

		httpRequest OBJECT-TYPE
		SYNTAX  CounterBasedGauge64 
		MAX-ACCESS read-only 
		STATUS current
		DESCRIPTION  "http request" 
		::={ acosSlbSslErrorS 61 } 

		illegalPadding OBJECT-TYPE
		SYNTAX  CounterBasedGauge64 
		MAX-ACCESS read-only 
		STATUS current
		DESCRIPTION  "illegal padding" 
		::={ acosSlbSslErrorS 62 } 

		inappropriateFallback OBJECT-TYPE
		SYNTAX  CounterBasedGauge64 
		MAX-ACCESS read-only 
		STATUS current
		DESCRIPTION  "inappropriate fallback" 
		::={ acosSlbSslErrorS 63 } 

		invalidChallengeLength OBJECT-TYPE
		SYNTAX  CounterBasedGauge64 
		MAX-ACCESS read-only 
		STATUS current
		DESCRIPTION  "invalid challenge length" 
		::={ acosSlbSslErrorS 64 } 

		invalidCommand OBJECT-TYPE
		SYNTAX  CounterBasedGauge64 
		MAX-ACCESS read-only 
		STATUS current
		DESCRIPTION  "invalid command" 
		::={ acosSlbSslErrorS 65 } 

		invalidPurpose OBJECT-TYPE
		SYNTAX  CounterBasedGauge64 
		MAX-ACCESS read-only 
		STATUS current
		DESCRIPTION  "invalid purpose" 
		::={ acosSlbSslErrorS 66 } 

		invalidStatusResponse OBJECT-TYPE
		SYNTAX  CounterBasedGauge64 
		MAX-ACCESS read-only 
		STATUS current
		DESCRIPTION  "invalid status response" 
		::={ acosSlbSslErrorS 67 } 

		invalidTrust OBJECT-TYPE
		SYNTAX  CounterBasedGauge64 
		MAX-ACCESS read-only 
		STATUS current
		DESCRIPTION  "invalid trust" 
		::={ acosSlbSslErrorS 68 } 

		keyArgTooLong OBJECT-TYPE
		SYNTAX  CounterBasedGauge64 
		MAX-ACCESS read-only 
		STATUS current
		DESCRIPTION  "key arg too long" 
		::={ acosSlbSslErrorS 69 } 

		krb5 OBJECT-TYPE
		SYNTAX  CounterBasedGauge64 
		MAX-ACCESS read-only 
		STATUS current
		DESCRIPTION  "krb5" 
		::={ acosSlbSslErrorS 70 } 

		krb5ClientCcPrincipal OBJECT-TYPE
		SYNTAX  CounterBasedGauge64 
		MAX-ACCESS read-only 
		STATUS current
		DESCRIPTION  "krb5 client cc principal" 
		::={ acosSlbSslErrorS 71 } 

		krb5ClientGetCred OBJECT-TYPE
		SYNTAX  CounterBasedGauge64 
		MAX-ACCESS read-only 
		STATUS current
		DESCRIPTION  "krb5 client get cred" 
		::={ acosSlbSslErrorS 72 } 

		krb5ClientInit OBJECT-TYPE
		SYNTAX  CounterBasedGauge64 
		MAX-ACCESS read-only 
		STATUS current
		DESCRIPTION  "krb5 client init" 
		::={ acosSlbSslErrorS 73 } 

		krb5ClientMkReq OBJECT-TYPE
		SYNTAX  CounterBasedGauge64 
		MAX-ACCESS read-only 
		STATUS current
		DESCRIPTION  "krb5 client mk_req" 
		::={ acosSlbSslErrorS 74 } 

		krb5ServerBadTicket OBJECT-TYPE
		SYNTAX  CounterBasedGauge64 
		MAX-ACCESS read-only 
		STATUS current
		DESCRIPTION  "krb5 server bad ticket" 
		::={ acosSlbSslErrorS 75 } 

		krb5ServerInit OBJECT-TYPE
		SYNTAX  CounterBasedGauge64 
		MAX-ACCESS read-only 
		STATUS current
		DESCRIPTION  "krb5 server init" 
		::={ acosSlbSslErrorS 76 } 

		krb5ServerRdReq OBJECT-TYPE
		SYNTAX  CounterBasedGauge64 
		MAX-ACCESS read-only 
		STATUS current
		DESCRIPTION  "krb5 server rd_req" 
		::={ acosSlbSslErrorS 77 } 

		krb5ServerTktExpired OBJECT-TYPE
		SYNTAX  CounterBasedGauge64 
		MAX-ACCESS read-only 
		STATUS current
		DESCRIPTION  "krb5 server tkt expired" 
		::={ acosSlbSslErrorS 78 } 

		krb5ServerTktNotYetValid OBJECT-TYPE
		SYNTAX  CounterBasedGauge64 
		MAX-ACCESS read-only 
		STATUS current
		DESCRIPTION  "krb5 server tkt not yet valid" 
		::={ acosSlbSslErrorS 79 } 

		krb5ServerTktSkew OBJECT-TYPE
		SYNTAX  CounterBasedGauge64 
		MAX-ACCESS read-only 
		STATUS current
		DESCRIPTION  "krb5 server tkt skew" 
		::={ acosSlbSslErrorS 80 } 

		lengthMismatch OBJECT-TYPE
		SYNTAX  CounterBasedGauge64 
		MAX-ACCESS read-only 
		STATUS current
		DESCRIPTION  "length mismatch" 
		::={ acosSlbSslErrorS 81 } 

		lengthTooShort OBJECT-TYPE
		SYNTAX  CounterBasedGauge64 
		MAX-ACCESS read-only 
		STATUS current
		DESCRIPTION  "length too short" 
		::={ acosSlbSslErrorS 82 } 

		libraryBug OBJECT-TYPE
		SYNTAX  CounterBasedGauge64 
		MAX-ACCESS read-only 
		STATUS current
		DESCRIPTION  "library bug" 
		::={ acosSlbSslErrorS 83 } 

		libraryHasNoCiphers OBJECT-TYPE
		SYNTAX  CounterBasedGauge64 
		MAX-ACCESS read-only 
		STATUS current
		DESCRIPTION  "library has no ciphers" 
		::={ acosSlbSslErrorS 84 } 

		mastKeyTooLong OBJECT-TYPE
		SYNTAX  CounterBasedGauge64 
		MAX-ACCESS read-only 
		STATUS current
		DESCRIPTION  "mast key too long" 
		::={ acosSlbSslErrorS 85 } 

		messageTooLong OBJECT-TYPE
		SYNTAX  CounterBasedGauge64 
		MAX-ACCESS read-only 
		STATUS current
		DESCRIPTION  "message too long" 
		::={ acosSlbSslErrorS 86 } 

		missingDhDsaCert OBJECT-TYPE
		SYNTAX  CounterBasedGauge64 
		MAX-ACCESS read-only 
		STATUS current
		DESCRIPTION  "missing dh dsa cert" 
		::={ acosSlbSslErrorS 87 } 

		missingDhKey OBJECT-TYPE
		SYNTAX  CounterBasedGauge64 
		MAX-ACCESS read-only 
		STATUS current
		DESCRIPTION  "missing dh key" 
		::={ acosSlbSslErrorS 88 } 

		missingDhRsaCert OBJECT-TYPE
		SYNTAX  CounterBasedGauge64 
		MAX-ACCESS read-only 
		STATUS current
		DESCRIPTION  "missing dh rsa cert" 
		::={ acosSlbSslErrorS 89 } 

		missingDsaSigningCert OBJECT-TYPE
		SYNTAX  CounterBasedGauge64 
		MAX-ACCESS read-only 
		STATUS current
		DESCRIPTION  "missing dsa signing cert" 
		::={ acosSlbSslErrorS 90 } 

		missingExportTmpDhKey OBJECT-TYPE
		SYNTAX  CounterBasedGauge64 
		MAX-ACCESS read-only 
		STATUS current
		DESCRIPTION  "missing export tmp dh key" 
		::={ acosSlbSslErrorS 91 } 

		missingExportTmpRsaKey OBJECT-TYPE
		SYNTAX  CounterBasedGauge64 
		MAX-ACCESS read-only 
		STATUS current
		DESCRIPTION  "missing export tmp rsa key" 
		::={ acosSlbSslErrorS 92 } 

		missingRsaCertificate OBJECT-TYPE
		SYNTAX  CounterBasedGauge64 
		MAX-ACCESS read-only 
		STATUS current
		DESCRIPTION  "missing rsa certificate" 
		::={ acosSlbSslErrorS 93 } 

		missingRsaEncryptingCert OBJECT-TYPE
		SYNTAX  CounterBasedGauge64 
		MAX-ACCESS read-only 
		STATUS current
		DESCRIPTION  "missing rsa encrypting cert" 
		::={ acosSlbSslErrorS 94 } 

		missingRsaSigningCert OBJECT-TYPE
		SYNTAX  CounterBasedGauge64 
		MAX-ACCESS read-only 
		STATUS current
		DESCRIPTION  "missing rsa signing cert" 
		::={ acosSlbSslErrorS 95 } 

		missingTmpDhKey OBJECT-TYPE
		SYNTAX  CounterBasedGauge64 
		MAX-ACCESS read-only 
		STATUS current
		DESCRIPTION  "missing tmp dh key" 
		::={ acosSlbSslErrorS 96 } 

		missingTmpRsaKey OBJECT-TYPE
		SYNTAX  CounterBasedGauge64 
		MAX-ACCESS read-only 
		STATUS current
		DESCRIPTION  "missing tmp rsa key" 
		::={ acosSlbSslErrorS 97 } 

		missingTmpRsaPkey OBJECT-TYPE
		SYNTAX  CounterBasedGauge64 
		MAX-ACCESS read-only 
		STATUS current
		DESCRIPTION  "missing tmp rsa pkey" 
		::={ acosSlbSslErrorS 98 } 

		missingVerifyMessage OBJECT-TYPE
		SYNTAX  CounterBasedGauge64 
		MAX-ACCESS read-only 
		STATUS current
		DESCRIPTION  "missing verify message" 
		::={ acosSlbSslErrorS 99 } 

		nonSslv2InitialPacket OBJECT-TYPE
		SYNTAX  CounterBasedGauge64 
		MAX-ACCESS read-only 
		STATUS current
		DESCRIPTION  "non sslv2 initial packet" 
		::={ acosSlbSslErrorS 100 } 

		noCertificatesReturned OBJECT-TYPE
		SYNTAX  CounterBasedGauge64 
		MAX-ACCESS read-only 
		STATUS current
		DESCRIPTION  "no certificates returned" 
		::={ acosSlbSslErrorS 101 } 

		noCertificateAssigned OBJECT-TYPE
		SYNTAX  CounterBasedGauge64 
		MAX-ACCESS read-only 
		STATUS current
		DESCRIPTION  "no certificate assigned" 
		::={ acosSlbSslErrorS 102 } 

		noCertificateReturned OBJECT-TYPE
		SYNTAX  CounterBasedGauge64 
		MAX-ACCESS read-only 
		STATUS current
		DESCRIPTION  "no certificate returned" 
		::={ acosSlbSslErrorS 103 } 

		noCertificateSet OBJECT-TYPE
		SYNTAX  CounterBasedGauge64 
		MAX-ACCESS read-only 
		STATUS current
		DESCRIPTION  "no certificate set" 
		::={ acosSlbSslErrorS 104 } 

		noCertificateSpecified OBJECT-TYPE
		SYNTAX  CounterBasedGauge64 
		MAX-ACCESS read-only 
		STATUS current
		DESCRIPTION  "no certificate specified" 
		::={ acosSlbSslErrorS 105 } 

		noCiphersAvailable OBJECT-TYPE
		SYNTAX  CounterBasedGauge64 
		MAX-ACCESS read-only 
		STATUS current
		DESCRIPTION  "no ciphers available" 
		::={ acosSlbSslErrorS 106 } 

		noCiphersPassed OBJECT-TYPE
		SYNTAX  CounterBasedGauge64 
		MAX-ACCESS read-only 
		STATUS current
		DESCRIPTION  "no ciphers passed" 
		::={ acosSlbSslErrorS 107 } 

		noCiphersSpecified OBJECT-TYPE
		SYNTAX  CounterBasedGauge64 
		MAX-ACCESS read-only 
		STATUS current
		DESCRIPTION  "no ciphers specified" 
		::={ acosSlbSslErrorS 108 } 

		noCipherList OBJECT-TYPE
		SYNTAX  CounterBasedGauge64 
		MAX-ACCESS read-only 
		STATUS current
		DESCRIPTION  "no cipher list" 
		::={ acosSlbSslErrorS 109 } 

		noCipherMatch OBJECT-TYPE
		SYNTAX  CounterBasedGauge64 
		MAX-ACCESS read-only 
		STATUS current
		DESCRIPTION  "no cipher match" 
		::={ acosSlbSslErrorS 110 } 

		noClientCertReceived OBJECT-TYPE
		SYNTAX  CounterBasedGauge64 
		MAX-ACCESS read-only 
		STATUS current
		DESCRIPTION  "no client cert received" 
		::={ acosSlbSslErrorS 111 } 

		noCompressionSpecified OBJECT-TYPE
		SYNTAX  CounterBasedGauge64 
		MAX-ACCESS read-only 
		STATUS current
		DESCRIPTION  "no compression specified" 
		::={ acosSlbSslErrorS 112 } 

		noMethodSpecified OBJECT-TYPE
		SYNTAX  CounterBasedGauge64 
		MAX-ACCESS read-only 
		STATUS current
		DESCRIPTION  "no method specified" 
		::={ acosSlbSslErrorS 113 } 

		noPrivatekey OBJECT-TYPE
		SYNTAX  CounterBasedGauge64 
		MAX-ACCESS read-only 
		STATUS current
		DESCRIPTION  "no privatekey" 
		::={ acosSlbSslErrorS 114 } 

		noPrivateKeyAssigned OBJECT-TYPE
		SYNTAX  CounterBasedGauge64 
		MAX-ACCESS read-only 
		STATUS current
		DESCRIPTION  "no private key assigned" 
		::={ acosSlbSslErrorS 115 } 

		noProtocolsAvailable OBJECT-TYPE
		SYNTAX  CounterBasedGauge64 
		MAX-ACCESS read-only 
		STATUS current
		DESCRIPTION  "no protocols available" 
		::={ acosSlbSslErrorS 116 } 

		noPublickey OBJECT-TYPE
		SYNTAX  CounterBasedGauge64 
		MAX-ACCESS read-only 
		STATUS current
		DESCRIPTION  "no publickey" 
		::={ acosSlbSslErrorS 117 } 

		noSharedCipher OBJECT-TYPE
		SYNTAX  CounterBasedGauge64 
		MAX-ACCESS read-only 
		STATUS current
		DESCRIPTION  "no shared cipher" 
		::={ acosSlbSslErrorS 118 } 

		noVerifyCallback OBJECT-TYPE
		SYNTAX  CounterBasedGauge64 
		MAX-ACCESS read-only 
		STATUS current
		DESCRIPTION  "no verify callback" 
		::={ acosSlbSslErrorS 119 } 

		nullSslCtx OBJECT-TYPE
		SYNTAX  CounterBasedGauge64 
		MAX-ACCESS read-only 
		STATUS current
		DESCRIPTION  "null ssl ctx" 
		::={ acosSlbSslErrorS 120 } 

		nullSslMethodPassed OBJECT-TYPE
		SYNTAX  CounterBasedGauge64 
		MAX-ACCESS read-only 
		STATUS current
		DESCRIPTION  "null ssl method passed" 
		::={ acosSlbSslErrorS 121 } 

		oldSessionCipherNotReturned OBJECT-TYPE
		SYNTAX  CounterBasedGauge64 
		MAX-ACCESS read-only 
		STATUS current
		DESCRIPTION  "old session cipher not returned" 
		::={ acosSlbSslErrorS 122 } 

		packetLengthTooLong OBJECT-TYPE
		SYNTAX  CounterBasedGauge64 
		MAX-ACCESS read-only 
		STATUS current
		DESCRIPTION  "packet length too long" 
		::={ acosSlbSslErrorS 123 } 

		pathTooLong OBJECT-TYPE
		SYNTAX  CounterBasedGauge64 
		MAX-ACCESS read-only 
		STATUS current
		DESCRIPTION  "path too long" 
		::={ acosSlbSslErrorS 124 } 

		peerDidNotReturnACertificate OBJECT-TYPE
		SYNTAX  CounterBasedGauge64 
		MAX-ACCESS read-only 
		STATUS current
		DESCRIPTION  "peer did not return a certificate" 
		::={ acosSlbSslErrorS 125 } 

		peerError OBJECT-TYPE
		SYNTAX  CounterBasedGauge64 
		MAX-ACCESS read-only 
		STATUS current
		DESCRIPTION  "peer error" 
		::={ acosSlbSslErrorS 126 } 

		peerErrorCertificate OBJECT-TYPE
		SYNTAX  CounterBasedGauge64 
		MAX-ACCESS read-only 
		STATUS current
		DESCRIPTION  "peer error certificate" 
		::={ acosSlbSslErrorS 127 } 

		peerErrorNoCertificate OBJECT-TYPE
		SYNTAX  CounterBasedGauge64 
		MAX-ACCESS read-only 
		STATUS current
		DESCRIPTION  "peer error no certificate" 
		::={ acosSlbSslErrorS 128 } 

		peerErrorNoCipher OBJECT-TYPE
		SYNTAX  CounterBasedGauge64 
		MAX-ACCESS read-only 
		STATUS current
		DESCRIPTION  "peer error no cipher" 
		::={ acosSlbSslErrorS 129 } 

		peerErrorUnsupportedCertificateType OBJECT-TYPE
		SYNTAX  CounterBasedGauge64 
		MAX-ACCESS read-only 
		STATUS current
		DESCRIPTION  "peer error unsupported certificate type" 
		::={ acosSlbSslErrorS 130 } 

		preMacLengthTooLong OBJECT-TYPE
		SYNTAX  CounterBasedGauge64 
		MAX-ACCESS read-only 
		STATUS current
		DESCRIPTION  "pre mac length too long" 
		::={ acosSlbSslErrorS 131 } 

		problemsMappingCipherFunctions OBJECT-TYPE
		SYNTAX  CounterBasedGauge64 
		MAX-ACCESS read-only 
		STATUS current
		DESCRIPTION  "problems mapping cipher functions" 
		::={ acosSlbSslErrorS 132 } 

		protocolIsShutdown OBJECT-TYPE
		SYNTAX  CounterBasedGauge64 
		MAX-ACCESS read-only 
		STATUS current
		DESCRIPTION  "protocol is shutdown" 
		::={ acosSlbSslErrorS 133 } 

		publicKeyEncryptError OBJECT-TYPE
		SYNTAX  CounterBasedGauge64 
		MAX-ACCESS read-only 
		STATUS current
		DESCRIPTION  "public key encrypt error" 
		::={ acosSlbSslErrorS 134 } 

		publicKeyIsNotRsa OBJECT-TYPE
		SYNTAX  CounterBasedGauge64 
		MAX-ACCESS read-only 
		STATUS current
		DESCRIPTION  "public key is not rsa" 
		::={ acosSlbSslErrorS 135 } 

		publicKeyNotRsa OBJECT-TYPE
		SYNTAX  CounterBasedGauge64 
		MAX-ACCESS read-only 
		STATUS current
		DESCRIPTION  "public key not rsa" 
		::={ acosSlbSslErrorS 136 } 

		readBioNotSet OBJECT-TYPE
		SYNTAX  CounterBasedGauge64 
		MAX-ACCESS read-only 
		STATUS current
		DESCRIPTION  "read bio not set" 
		::={ acosSlbSslErrorS 137 } 

		readWrongPacketType OBJECT-TYPE
		SYNTAX  CounterBasedGauge64 
		MAX-ACCESS read-only 
		STATUS current
		DESCRIPTION  "read wrong packet type" 
		::={ acosSlbSslErrorS 138 } 

		recordLengthMismatch OBJECT-TYPE
		SYNTAX  CounterBasedGauge64 
		MAX-ACCESS read-only 
		STATUS current
		DESCRIPTION  "record length mismatch" 
		::={ acosSlbSslErrorS 139 } 

		recordTooLarge OBJECT-TYPE
		SYNTAX  CounterBasedGauge64 
		MAX-ACCESS read-only 
		STATUS current
		DESCRIPTION  "record too large" 
		::={ acosSlbSslErrorS 140 } 

		recordTooSmall OBJECT-TYPE
		SYNTAX  CounterBasedGauge64 
		MAX-ACCESS read-only 
		STATUS current
		DESCRIPTION  "record too small" 
		::={ acosSlbSslErrorS 141 } 

		requiredCipherMissing OBJECT-TYPE
		SYNTAX  CounterBasedGauge64 
		MAX-ACCESS read-only 
		STATUS current
		DESCRIPTION  "required cipher missing" 
		::={ acosSlbSslErrorS 142 } 

		reuseCertLengthNotZero OBJECT-TYPE
		SYNTAX  CounterBasedGauge64 
		MAX-ACCESS read-only 
		STATUS current
		DESCRIPTION  "reuse cert length not zero" 
		::={ acosSlbSslErrorS 143 } 

		reuseCertTypeNotZero OBJECT-TYPE
		SYNTAX  CounterBasedGauge64 
		MAX-ACCESS read-only 
		STATUS current
		DESCRIPTION  "reuse cert type not zero" 
		::={ acosSlbSslErrorS 144 } 

		reuseCipherListNotZero OBJECT-TYPE
		SYNTAX  CounterBasedGauge64 
		MAX-ACCESS read-only 
		STATUS current
		DESCRIPTION  "reuse cipher list not zero" 
		::={ acosSlbSslErrorS 145 } 

		scsvReceivedWhenRenegotiating OBJECT-TYPE
		SYNTAX  CounterBasedGauge64 
		MAX-ACCESS read-only 
		STATUS current
		DESCRIPTION  "scsv received when renegotiating" 
		::={ acosSlbSslErrorS 146 } 

		sessionIdContextUninitialized OBJECT-TYPE
		SYNTAX  CounterBasedGauge64 
		MAX-ACCESS read-only 
		STATUS current
		DESCRIPTION  "session id context uninitialized" 
		::={ acosSlbSslErrorS 147 } 

		shortRead OBJECT-TYPE
		SYNTAX  CounterBasedGauge64 
		MAX-ACCESS read-only 
		STATUS current
		DESCRIPTION  "short read" 
		::={ acosSlbSslErrorS 148 } 

		signatureForNonSigningCertificate OBJECT-TYPE
		SYNTAX  CounterBasedGauge64 
		MAX-ACCESS read-only 
		STATUS current
		DESCRIPTION  "signature for non signing certificate" 
		::={ acosSlbSslErrorS 149 } 

		ssl23DoingSessionIdReuse OBJECT-TYPE
		SYNTAX  CounterBasedGauge64 
		MAX-ACCESS read-only 
		STATUS current
		DESCRIPTION  "ssl23 doing session id reuse" 
		::={ acosSlbSslErrorS 150 } 

		ssl2ConnectionIdTooLong OBJECT-TYPE
		SYNTAX  CounterBasedGauge64 
		MAX-ACCESS read-only 
		STATUS current
		DESCRIPTION  "ssl2 connection id too long" 
		::={ acosSlbSslErrorS 151 } 

		ssl3SessionIdTooLong OBJECT-TYPE
		SYNTAX  CounterBasedGauge64 
		MAX-ACCESS read-only 
		STATUS current
		DESCRIPTION  "ssl3 session id too long" 
		::={ acosSlbSslErrorS 152 } 

		ssl3SessionIdTooShort OBJECT-TYPE
		SYNTAX  CounterBasedGauge64 
		MAX-ACCESS read-only 
		STATUS current
		DESCRIPTION  "ssl3 session id too short" 
		::={ acosSlbSslErrorS 153 } 

		sslv3AlertBadCertificate OBJECT-TYPE
		SYNTAX  CounterBasedGauge64 
		MAX-ACCESS read-only 
		STATUS current
		DESCRIPTION  "sslv3 alert bad certificate" 
		::={ acosSlbSslErrorS 154 } 

		sslv3AlertBadRecordMac OBJECT-TYPE
		SYNTAX  CounterBasedGauge64 
		MAX-ACCESS read-only 
		STATUS current
		DESCRIPTION  "sslv3 alert bad record mac" 
		::={ acosSlbSslErrorS 155 } 

		sslv3AlertCertificateExpired OBJECT-TYPE
		SYNTAX  CounterBasedGauge64 
		MAX-ACCESS read-only 
		STATUS current
		DESCRIPTION  "sslv3 alert certificate expired" 
		::={ acosSlbSslErrorS 156 } 

		sslv3AlertCertificateRevoked OBJECT-TYPE
		SYNTAX  CounterBasedGauge64 
		MAX-ACCESS read-only 
		STATUS current
		DESCRIPTION  "sslv3 alert certificate revoked" 
		::={ acosSlbSslErrorS 157 } 

		sslv3AlertCertificateUnknown OBJECT-TYPE
		SYNTAX  CounterBasedGauge64 
		MAX-ACCESS read-only 
		STATUS current
		DESCRIPTION  "sslv3 alert certificate unknown" 
		::={ acosSlbSslErrorS 158 } 

		sslv3AlertDecompressionFailure OBJECT-TYPE
		SYNTAX  CounterBasedGauge64 
		MAX-ACCESS read-only 
		STATUS current
		DESCRIPTION  "sslv3 alert decompression failure" 
		::={ acosSlbSslErrorS 159 } 

		sslv3AlertHandshakeFailure OBJECT-TYPE
		SYNTAX  CounterBasedGauge64 
		MAX-ACCESS read-only 
		STATUS current
		DESCRIPTION  "sslv3 alert handshake failure" 
		::={ acosSlbSslErrorS 160 } 

		sslv3AlertIllegalParameter OBJECT-TYPE
		SYNTAX  CounterBasedGauge64 
		MAX-ACCESS read-only 
		STATUS current
		DESCRIPTION  "sslv3 alert illegal parameter" 
		::={ acosSlbSslErrorS 161 } 

		sslv3AlertNoCertificate OBJECT-TYPE
		SYNTAX  CounterBasedGauge64 
		MAX-ACCESS read-only 
		STATUS current
		DESCRIPTION  "sslv3 alert no certificate" 
		::={ acosSlbSslErrorS 162 } 

		sslv3AlertPeerErrorCert OBJECT-TYPE
		SYNTAX  CounterBasedGauge64 
		MAX-ACCESS read-only 
		STATUS current
		DESCRIPTION  "sslv3 alert peer error cert" 
		::={ acosSlbSslErrorS 163 } 

		sslv3AlertPeerErrorNoCert OBJECT-TYPE
		SYNTAX  CounterBasedGauge64 
		MAX-ACCESS read-only 
		STATUS current
		DESCRIPTION  "sslv3 alert peer error no cert" 
		::={ acosSlbSslErrorS 164 } 

		sslv3AlertPeerErrorNoCipher OBJECT-TYPE
		SYNTAX  CounterBasedGauge64 
		MAX-ACCESS read-only 
		STATUS current
		DESCRIPTION  "sslv3 alert peer error no cipher" 
		::={ acosSlbSslErrorS 165 } 

		sslv3AlertPeerErrorUnsuppCertType OBJECT-TYPE
		SYNTAX  CounterBasedGauge64 
		MAX-ACCESS read-only 
		STATUS current
		DESCRIPTION  "sslv3 alert peer error unsupp cert type" 
		::={ acosSlbSslErrorS 166 } 

		sslv3AlertUnexpectedMsg OBJECT-TYPE
		SYNTAX  CounterBasedGauge64 
		MAX-ACCESS read-only 
		STATUS current
		DESCRIPTION  "sslv3 alert unexpected msg" 
		::={ acosSlbSslErrorS 167 } 

		sslv3AlertUnknownRemoteErrType OBJECT-TYPE
		SYNTAX  CounterBasedGauge64 
		MAX-ACCESS read-only 
		STATUS current
		DESCRIPTION  "sslv3 alert unknown remote err type" 
		::={ acosSlbSslErrorS 168 } 

		sslv3AlertUnspportedCert OBJECT-TYPE
		SYNTAX  CounterBasedGauge64 
		MAX-ACCESS read-only 
		STATUS current
		DESCRIPTION  "sslv3 alert unspported cert" 
		::={ acosSlbSslErrorS 169 } 

		sslCtxHasNoDefaultSslVersion OBJECT-TYPE
		SYNTAX  CounterBasedGauge64 
		MAX-ACCESS read-only 
		STATUS current
		DESCRIPTION  "ssl ctx has no default ssl version" 
		::={ acosSlbSslErrorS 170 } 

		sslHandshakeFailure OBJECT-TYPE
		SYNTAX  CounterBasedGauge64 
		MAX-ACCESS read-only 
		STATUS current
		DESCRIPTION  "ssl handshake failure" 
		::={ acosSlbSslErrorS 171 } 

		sslLibraryHasNoCiphers OBJECT-TYPE
		SYNTAX  CounterBasedGauge64 
		MAX-ACCESS read-only 
		STATUS current
		DESCRIPTION  "ssl library has no ciphers" 
		::={ acosSlbSslErrorS 172 } 

		sslSessionIdCallbackFailed OBJECT-TYPE
		SYNTAX  CounterBasedGauge64 
		MAX-ACCESS read-only 
		STATUS current
		DESCRIPTION  "ssl session id callback failed" 
		::={ acosSlbSslErrorS 173 } 

		sslSessionIdConflict OBJECT-TYPE
		SYNTAX  CounterBasedGauge64 
		MAX-ACCESS read-only 
		STATUS current
		DESCRIPTION  "ssl session id conflict" 
		::={ acosSlbSslErrorS 174 } 

		sslSessionIdContextTooLong OBJECT-TYPE
		SYNTAX  CounterBasedGauge64 
		MAX-ACCESS read-only 
		STATUS current
		DESCRIPTION  "ssl session id context too long" 
		::={ acosSlbSslErrorS 175 } 

		sslSessionIdHasBadLength OBJECT-TYPE
		SYNTAX  CounterBasedGauge64 
		MAX-ACCESS read-only 
		STATUS current
		DESCRIPTION  "ssl session id has bad length" 
		::={ acosSlbSslErrorS 176 } 

		sslSessionIdIsDifferent OBJECT-TYPE
		SYNTAX  CounterBasedGauge64 
		MAX-ACCESS read-only 
		STATUS current
		DESCRIPTION  "ssl session id is different" 
		::={ acosSlbSslErrorS 177 } 

		tlsv1AlertAccessDenied OBJECT-TYPE
		SYNTAX  CounterBasedGauge64 
		MAX-ACCESS read-only 
		STATUS current
		DESCRIPTION  "tlsv1 alert access denied" 
		::={ acosSlbSslErrorS 178 } 

		tlsv1AlertDecodeError OBJECT-TYPE
		SYNTAX  CounterBasedGauge64 
		MAX-ACCESS read-only 
		STATUS current
		DESCRIPTION  "tlsv1 alert decode error" 
		::={ acosSlbSslErrorS 179 } 

		tlsv1AlertDecryptionFailed OBJECT-TYPE
		SYNTAX  CounterBasedGauge64 
		MAX-ACCESS read-only 
		STATUS current
		DESCRIPTION  "tlsv1 alert decryption failed" 
		::={ acosSlbSslErrorS 180 } 

		tlsv1AlertDecryptError OBJECT-TYPE
		SYNTAX  CounterBasedGauge64 
		MAX-ACCESS read-only 
		STATUS current
		DESCRIPTION  "tlsv1 alert decrypt error" 
		::={ acosSlbSslErrorS 181 } 

		tlsv1AlertExportRestriction OBJECT-TYPE
		SYNTAX  CounterBasedGauge64 
		MAX-ACCESS read-only 
		STATUS current
		DESCRIPTION  "tlsv1 alert export restriction" 
		::={ acosSlbSslErrorS 182 } 

		tlsv1AlertInsufficientSecurity OBJECT-TYPE
		SYNTAX  CounterBasedGauge64 
		MAX-ACCESS read-only 
		STATUS current
		DESCRIPTION  "tlsv1 alert insufficient security" 
		::={ acosSlbSslErrorS 183 } 

		tlsv1AlertInternalError OBJECT-TYPE
		SYNTAX  CounterBasedGauge64 
		MAX-ACCESS read-only 
		STATUS current
		DESCRIPTION  "tlsv1 alert internal error" 
		::={ acosSlbSslErrorS 184 } 

		tlsv1AlertNoRenegotiation OBJECT-TYPE
		SYNTAX  CounterBasedGauge64 
		MAX-ACCESS read-only 
		STATUS current
		DESCRIPTION  "tlsv1 alert no renegotiation" 
		::={ acosSlbSslErrorS 185 } 

		tlsv1AlertProtocolVersion OBJECT-TYPE
		SYNTAX  CounterBasedGauge64 
		MAX-ACCESS read-only 
		STATUS current
		DESCRIPTION  "tlsv1 alert protocol version" 
		::={ acosSlbSslErrorS 186 } 

		tlsv1AlertRecordOverflow OBJECT-TYPE
		SYNTAX  CounterBasedGauge64 
		MAX-ACCESS read-only 
		STATUS current
		DESCRIPTION  "tlsv1 alert record overflow" 
		::={ acosSlbSslErrorS 187 } 

		tlsv1AlertUnknownCa OBJECT-TYPE
		SYNTAX  CounterBasedGauge64 
		MAX-ACCESS read-only 
		STATUS current
		DESCRIPTION  "tlsv1 alert unknown ca" 
		::={ acosSlbSslErrorS 188 } 

		tlsv1AlertUserCancelled OBJECT-TYPE
		SYNTAX  CounterBasedGauge64 
		MAX-ACCESS read-only 
		STATUS current
		DESCRIPTION  "tlsv1 alert user cancelled" 
		::={ acosSlbSslErrorS 189 } 

		tlsClientCertReqWithAnonCipher OBJECT-TYPE
		SYNTAX  CounterBasedGauge64 
		MAX-ACCESS read-only 
		STATUS current
		DESCRIPTION  "tls client cert req with anon cipher" 
		::={ acosSlbSslErrorS 190 } 

		tlsPeerDidNotRespondWithCertList OBJECT-TYPE
		SYNTAX  CounterBasedGauge64 
		MAX-ACCESS read-only 
		STATUS current
		DESCRIPTION  "tls peer did not respond with cert list" 
		::={ acosSlbSslErrorS 191 } 

		tlsRsaEncryptedValueLengthIsWrong OBJECT-TYPE
		SYNTAX  CounterBasedGauge64 
		MAX-ACCESS read-only 
		STATUS current
		DESCRIPTION  "tls rsa encrypted value length is wrong" 
		::={ acosSlbSslErrorS 192 } 

		triedToUseUnsupportedCipher OBJECT-TYPE
		SYNTAX  CounterBasedGauge64 
		MAX-ACCESS read-only 
		STATUS current
		DESCRIPTION  "tried to use unsupported cipher" 
		::={ acosSlbSslErrorS 193 } 

		unableToDecodeDhCerts OBJECT-TYPE
		SYNTAX  CounterBasedGauge64 
		MAX-ACCESS read-only 
		STATUS current
		DESCRIPTION  "unable to decode dh certs" 
		::={ acosSlbSslErrorS 194 } 

		unableToExtractPublicKey OBJECT-TYPE
		SYNTAX  CounterBasedGauge64 
		MAX-ACCESS read-only 
		STATUS current
		DESCRIPTION  "unable to extract public key" 
		::={ acosSlbSslErrorS 195 } 

		unableToFindDhParameters OBJECT-TYPE
		SYNTAX  CounterBasedGauge64 
		MAX-ACCESS read-only 
		STATUS current
		DESCRIPTION  "unable to find dh parameters" 
		::={ acosSlbSslErrorS 196 } 

		unableToFindPublicKeyParameters OBJECT-TYPE
		SYNTAX  CounterBasedGauge64 
		MAX-ACCESS read-only 
		STATUS current
		DESCRIPTION  "unable to find public key parameters" 
		::={ acosSlbSslErrorS 197 } 

		unableToFindSslMethod OBJECT-TYPE
		SYNTAX  CounterBasedGauge64 
		MAX-ACCESS read-only 
		STATUS current
		DESCRIPTION  "unable to find ssl method" 
		::={ acosSlbSslErrorS 198 } 

		unableToLoadSsl2Md5Routines OBJECT-TYPE
		SYNTAX  CounterBasedGauge64 
		MAX-ACCESS read-only 
		STATUS current
		DESCRIPTION  "unable to load ssl2 md5 routines" 
		::={ acosSlbSslErrorS 199 } 

		unableToLoadSsl3Md5Routines OBJECT-TYPE
		SYNTAX  CounterBasedGauge64 
		MAX-ACCESS read-only 
		STATUS current
		DESCRIPTION  "unable to load ssl3 md5 routines" 
		::={ acosSlbSslErrorS 200 } 

		unableToLoadSsl3Sha1Routines OBJECT-TYPE
		SYNTAX  CounterBasedGauge64 
		MAX-ACCESS read-only 
		STATUS current
		DESCRIPTION  "unable to load ssl3 sha1 routines" 
		::={ acosSlbSslErrorS 201 } 

		unexpectedMessage OBJECT-TYPE
		SYNTAX  CounterBasedGauge64 
		MAX-ACCESS read-only 
		STATUS current
		DESCRIPTION  "unexpected message" 
		::={ acosSlbSslErrorS 202 } 

		unexpectedRecord OBJECT-TYPE
		SYNTAX  CounterBasedGauge64 
		MAX-ACCESS read-only 
		STATUS current
		DESCRIPTION  "unexpected record" 
		::={ acosSlbSslErrorS 203 } 

		uninitialized OBJECT-TYPE
		SYNTAX  CounterBasedGauge64 
		MAX-ACCESS read-only 
		STATUS current
		DESCRIPTION  "uninitialized" 
		::={ acosSlbSslErrorS 204 } 

		unknownAlertType OBJECT-TYPE
		SYNTAX  CounterBasedGauge64 
		MAX-ACCESS read-only 
		STATUS current
		DESCRIPTION  "unknown alert type" 
		::={ acosSlbSslErrorS 205 } 

		unknownCertificateType OBJECT-TYPE
		SYNTAX  CounterBasedGauge64 
		MAX-ACCESS read-only 
		STATUS current
		DESCRIPTION  "unknown certificate type" 
		::={ acosSlbSslErrorS 206 } 

		unknownCipherReturned OBJECT-TYPE
		SYNTAX  CounterBasedGauge64 
		MAX-ACCESS read-only 
		STATUS current
		DESCRIPTION  "unknown cipher returned" 
		::={ acosSlbSslErrorS 207 } 

		unknownCipherType OBJECT-TYPE
		SYNTAX  CounterBasedGauge64 
		MAX-ACCESS read-only 
		STATUS current
		DESCRIPTION  "unknown cipher type" 
		::={ acosSlbSslErrorS 208 } 

		unknownKeyExchangeType OBJECT-TYPE
		SYNTAX  CounterBasedGauge64 
		MAX-ACCESS read-only 
		STATUS current
		DESCRIPTION  "unknown key exchange type" 
		::={ acosSlbSslErrorS 209 } 

		unknownPkeyType OBJECT-TYPE
		SYNTAX  CounterBasedGauge64 
		MAX-ACCESS read-only 
		STATUS current
		DESCRIPTION  "unknown pkey type" 
		::={ acosSlbSslErrorS 210 } 

		unknownProtocol OBJECT-TYPE
		SYNTAX  CounterBasedGauge64 
		MAX-ACCESS read-only 
		STATUS current
		DESCRIPTION  "unknown protocol" 
		::={ acosSlbSslErrorS 211 } 

		unknownRemoteErrorType OBJECT-TYPE
		SYNTAX  CounterBasedGauge64 
		MAX-ACCESS read-only 
		STATUS current
		DESCRIPTION  "unknown remote error type" 
		::={ acosSlbSslErrorS 212 } 

		unknownSslVersion OBJECT-TYPE
		SYNTAX  CounterBasedGauge64 
		MAX-ACCESS read-only 
		STATUS current
		DESCRIPTION  "unknown ssl version" 
		::={ acosSlbSslErrorS 213 } 

		unknownState OBJECT-TYPE
		SYNTAX  CounterBasedGauge64 
		MAX-ACCESS read-only 
		STATUS current
		DESCRIPTION  "unknown state" 
		::={ acosSlbSslErrorS 214 } 

		unsupportedCipher OBJECT-TYPE
		SYNTAX  CounterBasedGauge64 
		MAX-ACCESS read-only 
		STATUS current
		DESCRIPTION  "unsupported cipher" 
		::={ acosSlbSslErrorS 215 } 

		unsupportedCompressionAlgorithm OBJECT-TYPE
		SYNTAX  CounterBasedGauge64 
		MAX-ACCESS read-only 
		STATUS current
		DESCRIPTION  "unsupported compression algorithm" 
		::={ acosSlbSslErrorS 216 } 

		unsupportedOption OBJECT-TYPE
		SYNTAX  CounterBasedGauge64 
		MAX-ACCESS read-only 
		STATUS current
		DESCRIPTION  "unsupported option" 
		::={ acosSlbSslErrorS 217 } 

		unsupportedProtocol OBJECT-TYPE
		SYNTAX  CounterBasedGauge64 
		MAX-ACCESS read-only 
		STATUS current
		DESCRIPTION  "unsupported protocol" 
		::={ acosSlbSslErrorS 218 } 

		unsupportedSslVersion OBJECT-TYPE
		SYNTAX  CounterBasedGauge64 
		MAX-ACCESS read-only 
		STATUS current
		DESCRIPTION  "unsupported ssl version" 
		::={ acosSlbSslErrorS 219 } 

		unsupportedStatusType OBJECT-TYPE
		SYNTAX  CounterBasedGauge64 
		MAX-ACCESS read-only 
		STATUS current
		DESCRIPTION  "unsupported status type" 
		::={ acosSlbSslErrorS 220 } 

		writeBioNotSet OBJECT-TYPE
		SYNTAX  CounterBasedGauge64 
		MAX-ACCESS read-only 
		STATUS current
		DESCRIPTION  "write bio not set" 
		::={ acosSlbSslErrorS 221 } 

		wrongCipherReturned OBJECT-TYPE
		SYNTAX  CounterBasedGauge64 
		MAX-ACCESS read-only 
		STATUS current
		DESCRIPTION  "wrong cipher returned" 
		::={ acosSlbSslErrorS 222 } 

		wrongMessageType OBJECT-TYPE
		SYNTAX  CounterBasedGauge64 
		MAX-ACCESS read-only 
		STATUS current
		DESCRIPTION  "wrong message type" 
		::={ acosSlbSslErrorS 223 } 

		wrongCounterOfKeyBits OBJECT-TYPE
		SYNTAX  CounterBasedGauge64 
		MAX-ACCESS read-only 
		STATUS current
		DESCRIPTION  "wrong counter of key bits" 
		::={ acosSlbSslErrorS 224 } 

		wrongSignatureLength OBJECT-TYPE
		SYNTAX  CounterBasedGauge64 
		MAX-ACCESS read-only 
		STATUS current
		DESCRIPTION  "wrong signature length" 
		::={ acosSlbSslErrorS 225 } 

		wrongSignatureSize OBJECT-TYPE
		SYNTAX  CounterBasedGauge64 
		MAX-ACCESS read-only 
		STATUS current
		DESCRIPTION  "wrong signature size" 
		::={ acosSlbSslErrorS 226 } 

		wrongSslVersion OBJECT-TYPE
		SYNTAX  CounterBasedGauge64 
		MAX-ACCESS read-only 
		STATUS current
		DESCRIPTION  "wrong ssl version" 
		::={ acosSlbSslErrorS 227 } 

		wrongVersionCounter OBJECT-TYPE
		SYNTAX  CounterBasedGauge64 
		MAX-ACCESS read-only 
		STATUS current
		DESCRIPTION  "wrong version counter" 
		::={ acosSlbSslErrorS 228 } 

		x509Lib OBJECT-TYPE
		SYNTAX  CounterBasedGauge64 
		MAX-ACCESS read-only 
		STATUS current
		DESCRIPTION  "x509 lib" 
		::={ acosSlbSslErrorS 229 } 

		x509VerificationSetupProblems OBJECT-TYPE
		SYNTAX  CounterBasedGauge64 
		MAX-ACCESS read-only 
		STATUS current
		DESCRIPTION  "x509 verification setup problems" 
		::={ acosSlbSslErrorS 230 } 

		clienthelloTlsext OBJECT-TYPE
		SYNTAX  CounterBasedGauge64 
		MAX-ACCESS read-only 
		STATUS current
		DESCRIPTION  "clienthello tlsext" 
		::={ acosSlbSslErrorS 231 } 

		parseTlsext OBJECT-TYPE
		SYNTAX  CounterBasedGauge64 
		MAX-ACCESS read-only 
		STATUS current
		DESCRIPTION  "parse tlsext" 
		::={ acosSlbSslErrorS 232 } 

		serverhelloTlsext OBJECT-TYPE
		SYNTAX  CounterBasedGauge64 
		MAX-ACCESS read-only 
		STATUS current
		DESCRIPTION  "serverhello tlsext" 
		::={ acosSlbSslErrorS 233 } 

		ssl3ExtInvalidServername OBJECT-TYPE
		SYNTAX  CounterBasedGauge64 
		MAX-ACCESS read-only 
		STATUS current
		DESCRIPTION  "ssl3 ext invalid servername" 
		::={ acosSlbSslErrorS 234 } 

		ssl3ExtInvalidServernameType OBJECT-TYPE
		SYNTAX  CounterBasedGauge64 
		MAX-ACCESS read-only 
		STATUS current
		DESCRIPTION  "ssl3 ext invalid servername type" 
		::={ acosSlbSslErrorS 235 } 

		multipleSgcRestarts OBJECT-TYPE
		SYNTAX  CounterBasedGauge64 
		MAX-ACCESS read-only 
		STATUS current
		DESCRIPTION  "multiple sgc restarts" 
		::={ acosSlbSslErrorS 236 } 

		tlsInvalidEcpointformatList OBJECT-TYPE
		SYNTAX  CounterBasedGauge64 
		MAX-ACCESS read-only 
		STATUS current
		DESCRIPTION  "tls invalid ecpointformat list" 
		::={ acosSlbSslErrorS 237 } 

		badEccCert OBJECT-TYPE
		SYNTAX  CounterBasedGauge64 
		MAX-ACCESS read-only 
		STATUS current
		DESCRIPTION  "bad ecc cert" 
		::={ acosSlbSslErrorS 238 } 

		badEcdsaSig OBJECT-TYPE
		SYNTAX  CounterBasedGauge64 
		MAX-ACCESS read-only 
		STATUS current
		DESCRIPTION  "bad ecdsa sig" 
		::={ acosSlbSslErrorS 239 } 

		badEcpoint OBJECT-TYPE
		SYNTAX  CounterBasedGauge64 
		MAX-ACCESS read-only 
		STATUS current
		DESCRIPTION  "bad ecpoint" 
		::={ acosSlbSslErrorS 240 } 

		cookieMismatch OBJECT-TYPE
		SYNTAX  CounterBasedGauge64 
		MAX-ACCESS read-only 
		STATUS current
		DESCRIPTION  "cookie mismatch" 
		::={ acosSlbSslErrorS 241 } 

		unsupportedEllipticCurve OBJECT-TYPE
		SYNTAX  CounterBasedGauge64 
		MAX-ACCESS read-only 
		STATUS current
		DESCRIPTION  "unsupported elliptic curve" 
		::={ acosSlbSslErrorS 242 } 

		noRequiredDigest OBJECT-TYPE
		SYNTAX  CounterBasedGauge64 
		MAX-ACCESS read-only 
		STATUS current
		DESCRIPTION  "no required digest" 
		::={ acosSlbSslErrorS 243 } 

		unsupportedDigestType OBJECT-TYPE
		SYNTAX  CounterBasedGauge64 
		MAX-ACCESS read-only 
		STATUS current
		DESCRIPTION  "unsupported digest type" 
		::={ acosSlbSslErrorS 244 } 

		badHandshakeLength OBJECT-TYPE
		SYNTAX  CounterBasedGauge64 
		MAX-ACCESS read-only 
		STATUS current
		DESCRIPTION  "bad handshake length" 
		::={ acosSlbSslErrorS 245 } 

acosSlbSslCertRevoke                OBJECT IDENTIFIER ::= { acosSlb 12 }
acosSlbSslCertRevokeS               OBJECT IDENTIFIER ::= { acosSlbSslCertRevoke 1 }

		ocspStaplingResponseGood OBJECT-TYPE
		SYNTAX  CounterBasedGauge64 
		MAX-ACCESS read-only 
		STATUS current
		DESCRIPTION  "OCSP stapling response good" 
		::={ acosSlbSslCertRevokeS 1 } 

		ocspChainStatusGood OBJECT-TYPE
		SYNTAX  CounterBasedGauge64 
		MAX-ACCESS read-only 
		STATUS current
		DESCRIPTION  "Certificate chain status good" 
		::={ acosSlbSslCertRevokeS 2 } 

		ocspChainStatusRevoked OBJECT-TYPE
		SYNTAX  CounterBasedGauge64 
		MAX-ACCESS read-only 
		STATUS current
		DESCRIPTION  "Certificate chain status revoked" 
		::={ acosSlbSslCertRevokeS 3 } 

		ocspChainStatusUnknown OBJECT-TYPE
		SYNTAX  CounterBasedGauge64 
		MAX-ACCESS read-only 
		STATUS current
		DESCRIPTION  "Certificate chain status unknown" 
		::={ acosSlbSslCertRevokeS 4 } 

		ocspRequest OBJECT-TYPE
		SYNTAX  CounterBasedGauge64 
		MAX-ACCESS read-only 
		STATUS current
		DESCRIPTION  "OCSP requests" 
		::={ acosSlbSslCertRevokeS 5 } 

		ocspResponse OBJECT-TYPE
		SYNTAX  CounterBasedGauge64 
		MAX-ACCESS read-only 
		STATUS current
		DESCRIPTION  "OCSP responses" 
		::={ acosSlbSslCertRevokeS 6 } 

		ocspConnectionError OBJECT-TYPE
		SYNTAX  CounterBasedGauge64 
		MAX-ACCESS read-only 
		STATUS current
		DESCRIPTION  "OCSP connection error" 
		::={ acosSlbSslCertRevokeS 7 } 

		ocspUriNotFound OBJECT-TYPE
		SYNTAX  CounterBasedGauge64 
		MAX-ACCESS read-only 
		STATUS current
		DESCRIPTION  "OCSP URI not found" 
		::={ acosSlbSslCertRevokeS 8 } 

		ocspUriHttps OBJECT-TYPE
		SYNTAX  CounterBasedGauge64 
		MAX-ACCESS read-only 
		STATUS current
		DESCRIPTION  "Log OCSP URI https" 
		::={ acosSlbSslCertRevokeS 9 } 

		ocspUriUnsupported OBJECT-TYPE
		SYNTAX  CounterBasedGauge64 
		MAX-ACCESS read-only 
		STATUS current
		DESCRIPTION  "OCSP URI unsupported" 
		::={ acosSlbSslCertRevokeS 10 } 

		ocspResponseStatusGood OBJECT-TYPE
		SYNTAX  CounterBasedGauge64 
		MAX-ACCESS read-only 
		STATUS current
		DESCRIPTION  "OCSP response status good" 
		::={ acosSlbSslCertRevokeS 11 } 

		ocspResponseStatusRevoked OBJECT-TYPE
		SYNTAX  CounterBasedGauge64 
		MAX-ACCESS read-only 
		STATUS current
		DESCRIPTION  "OCSP response status revoked" 
		::={ acosSlbSslCertRevokeS 12 } 

		ocspResponseStatusUnknown OBJECT-TYPE
		SYNTAX  CounterBasedGauge64 
		MAX-ACCESS read-only 
		STATUS current
		DESCRIPTION  "OCSP response status unknown" 
		::={ acosSlbSslCertRevokeS 13 } 

		ocspCacheStatusGood OBJECT-TYPE
		SYNTAX  CounterBasedGauge64 
		MAX-ACCESS read-only 
		STATUS current
		DESCRIPTION  "OCSP cache status good" 
		::={ acosSlbSslCertRevokeS 14 } 

		ocspCacheStatusRevoked OBJECT-TYPE
		SYNTAX  CounterBasedGauge64 
		MAX-ACCESS read-only 
		STATUS current
		DESCRIPTION  "OCSP cache status revoked" 
		::={ acosSlbSslCertRevokeS 15 } 

		ocspCacheMiss OBJECT-TYPE
		SYNTAX  CounterBasedGauge64 
		MAX-ACCESS read-only 
		STATUS current
		DESCRIPTION  "OCSP cache miss" 
		::={ acosSlbSslCertRevokeS 16 } 

		ocspCacheExpired OBJECT-TYPE
		SYNTAX  CounterBasedGauge64 
		MAX-ACCESS read-only 
		STATUS current
		DESCRIPTION  "OCSP cache expired" 
		::={ acosSlbSslCertRevokeS 17 } 

		ocspOtherError OBJECT-TYPE
		SYNTAX  CounterBasedGauge64 
		MAX-ACCESS read-only 
		STATUS current
		DESCRIPTION  "Log OCSP other errors" 
		::={ acosSlbSslCertRevokeS 18 } 

		ocspResponseNoNonce OBJECT-TYPE
		SYNTAX  CounterBasedGauge64 
		MAX-ACCESS read-only 
		STATUS current
		DESCRIPTION  "Log OCSP other errors" 
		::={ acosSlbSslCertRevokeS 19 } 

		ocspResponseNonceError OBJECT-TYPE
		SYNTAX  CounterBasedGauge64 
		MAX-ACCESS read-only 
		STATUS current
		DESCRIPTION  "Log OCSP other errors" 
		::={ acosSlbSslCertRevokeS 20 } 

		crlRequest OBJECT-TYPE
		SYNTAX  CounterBasedGauge64 
		MAX-ACCESS read-only 
		STATUS current
		DESCRIPTION  "CRL requests" 
		::={ acosSlbSslCertRevokeS 21 } 

		crlResponse OBJECT-TYPE
		SYNTAX  CounterBasedGauge64 
		MAX-ACCESS read-only 
		STATUS current
		DESCRIPTION  "CRL responses" 
		::={ acosSlbSslCertRevokeS 22 } 

		crlConnectionError OBJECT-TYPE
		SYNTAX  CounterBasedGauge64 
		MAX-ACCESS read-only 
		STATUS current
		DESCRIPTION  "CRL connection errors" 
		::={ acosSlbSslCertRevokeS 23 } 

		crlUriNotFound OBJECT-TYPE
		SYNTAX  CounterBasedGauge64 
		MAX-ACCESS read-only 
		STATUS current
		DESCRIPTION  "CRL URI not found" 
		::={ acosSlbSslCertRevokeS 24 } 

		crlUriHttps OBJECT-TYPE
		SYNTAX  CounterBasedGauge64 
		MAX-ACCESS read-only 
		STATUS current
		DESCRIPTION  "CRL URI https" 
		::={ acosSlbSslCertRevokeS 25 } 

		crlUriUnsupported OBJECT-TYPE
		SYNTAX  CounterBasedGauge64 
		MAX-ACCESS read-only 
		STATUS current
		DESCRIPTION  "CRL URI unsupported" 
		::={ acosSlbSslCertRevokeS 26 } 

		crlResponseStatusGood OBJECT-TYPE
		SYNTAX  CounterBasedGauge64 
		MAX-ACCESS read-only 
		STATUS current
		DESCRIPTION  "CRL response status good" 
		::={ acosSlbSslCertRevokeS 27 } 

		crlResponseStatusRevoked OBJECT-TYPE
		SYNTAX  CounterBasedGauge64 
		MAX-ACCESS read-only 
		STATUS current
		DESCRIPTION  "CRL response status revoked" 
		::={ acosSlbSslCertRevokeS 28 } 

		crlResponseStatusUnknown OBJECT-TYPE
		SYNTAX  CounterBasedGauge64 
		MAX-ACCESS read-only 
		STATUS current
		DESCRIPTION  "CRL response status unknown" 
		::={ acosSlbSslCertRevokeS 29 } 

		crlCacheStatusGood OBJECT-TYPE
		SYNTAX  CounterBasedGauge64 
		MAX-ACCESS read-only 
		STATUS current
		DESCRIPTION  "CRL cache status good" 
		::={ acosSlbSslCertRevokeS 30 } 

		crlCacheStatusRevoked OBJECT-TYPE
		SYNTAX  CounterBasedGauge64 
		MAX-ACCESS read-only 
		STATUS current
		DESCRIPTION  "CRL cache status revoked" 
		::={ acosSlbSslCertRevokeS 31 } 

		crlOtherError OBJECT-TYPE
		SYNTAX  CounterBasedGauge64 
		MAX-ACCESS read-only 
		STATUS current
		DESCRIPTION  "CRL other errors" 
		::={ acosSlbSslCertRevokeS 32 } 

acosSlbPerf                         OBJECT IDENTIFIER ::= { acosSlb 13 }
acosSlbPerfS                        OBJECT IDENTIFIER ::= { acosSlbPerf 1 }

		totalThroughputBitsPerSec OBJECT-TYPE
		SYNTAX  CounterBasedGauge64 
		MAX-ACCESS read-only 
		STATUS current
		DESCRIPTION  "Total Throughput in bits/sec" 
		::={ acosSlbPerfS 1 } 

		l4ConnsPerSec OBJECT-TYPE
		SYNTAX  CounterBasedGauge64 
		MAX-ACCESS read-only 
		STATUS current
		DESCRIPTION  "L4 Connections/sec" 
		::={ acosSlbPerfS 2 } 

		l7ConnsPerSec OBJECT-TYPE
		SYNTAX  CounterBasedGauge64 
		MAX-ACCESS read-only 
		STATUS current
		DESCRIPTION  "L7 Connections/sec" 
		::={ acosSlbPerfS 3 } 

		l7TransPerSec OBJECT-TYPE
		SYNTAX  CounterBasedGauge64 
		MAX-ACCESS read-only 
		STATUS current
		DESCRIPTION  "L7 Transactions/sec" 
		::={ acosSlbPerfS 4 } 

		sslConnsPerSec OBJECT-TYPE
		SYNTAX  CounterBasedGauge64 
		MAX-ACCESS read-only 
		STATUS current
		DESCRIPTION  "SSL Connections/sec" 
		::={ acosSlbPerfS 5 } 

		ipNatConnsPerSec OBJECT-TYPE
		SYNTAX  CounterBasedGauge64 
		MAX-ACCESS read-only 
		STATUS current
		DESCRIPTION  "IP NAT Connections/sec" 
		::={ acosSlbPerfS 6 } 

		totalNewConnsPerSec OBJECT-TYPE
		SYNTAX  CounterBasedGauge64 
		MAX-ACCESS read-only 
		STATUS current
		DESCRIPTION  "Total New Connections Established/sec" 
		::={ acosSlbPerfS 7 } 

		totalCurrConns OBJECT-TYPE
		SYNTAX  CounterBasedGauge64 
		MAX-ACCESS read-only 
		STATUS current
		DESCRIPTION  "Total Current Established Connections" 
		::={ acosSlbPerfS 8 } 

		l4Bandwidth OBJECT-TYPE
		SYNTAX  CounterBasedGauge64 
		MAX-ACCESS read-only 
		STATUS current
		DESCRIPTION  "L4 Bandwidth in bits/sec" 
		::={ acosSlbPerfS 9 } 

		l7Bandwidth OBJECT-TYPE
		SYNTAX  CounterBasedGauge64 
		MAX-ACCESS read-only 
		STATUS current
		DESCRIPTION  "L7 Bandwidth in bits/sec" 
		::={ acosSlbPerfS 10 } 

		servSslConnsPerSec OBJECT-TYPE
		SYNTAX  CounterBasedGauge64 
		MAX-ACCESS read-only 
		STATUS current
		DESCRIPTION  "Server SSL Connections/sec" 
		::={ acosSlbPerfS 11 } 

		fwConnsPerSec OBJECT-TYPE
		SYNTAX  CounterBasedGauge64 
		MAX-ACCESS read-only 
		STATUS current
		DESCRIPTION  "FW Connections/sec" 
		::={ acosSlbPerfS 12 } 

		gifwConnsPerSec OBJECT-TYPE
		SYNTAX  CounterBasedGauge64 
		MAX-ACCESS read-only 
		STATUS current
		DESCRIPTION  "GiFW Connections/sec" 
		::={ acosSlbPerfS 13 } 

		l7ProxyConnsPerSec OBJECT-TYPE
		SYNTAX  CounterBasedGauge64 
		MAX-ACCESS read-only 
		STATUS current
		DESCRIPTION  "L7 Proxy Connections/sec" 
		::={ acosSlbPerfS 14 } 

		l7ProxyTransPerSec OBJECT-TYPE
		SYNTAX  CounterBasedGauge64 
		MAX-ACCESS read-only 
		STATUS current
		DESCRIPTION  "L7 Proxy Transactions/sec" 
		::={ acosSlbPerfS 15 } 

acosSlbSslForwardProxy              OBJECT IDENTIFIER ::= { acosSlb 17 }
acosSlbSslForwardProxyS             OBJECT IDENTIFIER ::= { acosSlbSslForwardProxy 1 }

		certCreate OBJECT-TYPE
		SYNTAX  CounterBasedGauge64 
		MAX-ACCESS read-only 
		STATUS current
		DESCRIPTION  "Certificates created" 
		::={ acosSlbSslForwardProxyS 1 } 

		certExpr OBJECT-TYPE
		SYNTAX  CounterBasedGauge64 
		MAX-ACCESS read-only 
		STATUS current
		DESCRIPTION  "Certificates expired" 
		::={ acosSlbSslForwardProxyS 2 } 

		certHit OBJECT-TYPE
		SYNTAX  CounterBasedGauge64 
		MAX-ACCESS read-only 
		STATUS current
		DESCRIPTION  "Certificate cache hits" 
		::={ acosSlbSslForwardProxyS 3 } 

		certMiss OBJECT-TYPE
		SYNTAX  CounterBasedGauge64 
		MAX-ACCESS read-only 
		STATUS current
		DESCRIPTION  "Certificate cache miss" 
		::={ acosSlbSslForwardProxyS 4 } 

		connBypass OBJECT-TYPE
		SYNTAX  CounterBasedGauge64 
		MAX-ACCESS read-only 
		STATUS current
		DESCRIPTION  "Connections bypassed" 
		::={ acosSlbSslForwardProxyS 5 } 

		connInspect OBJECT-TYPE
		SYNTAX  CounterBasedGauge64 
		MAX-ACCESS read-only 
		STATUS current
		DESCRIPTION  "Connections inspected" 
		::={ acosSlbSslForwardProxyS 6 } 

		bypassFailsafeSslSessions OBJECT-TYPE
		SYNTAX  CounterBasedGauge64 
		MAX-ACCESS read-only 
		STATUS current
		DESCRIPTION  "Bypass Failsafe SSL sessions" 
		::={ acosSlbSslForwardProxyS 7 } 

		bypassSniSessions OBJECT-TYPE
		SYNTAX  CounterBasedGauge64 
		MAX-ACCESS read-only 
		STATUS current
		DESCRIPTION  "Bypass SNI sessions" 
		::={ acosSlbSslForwardProxyS 8 } 

		bypassClientAuthSessions OBJECT-TYPE
		SYNTAX  CounterBasedGauge64 
		MAX-ACCESS read-only 
		STATUS current
		DESCRIPTION  "Bypass Client Auth sessions" 
		::={ acosSlbSslForwardProxyS 9 } 

		failedInSslHandshakes OBJECT-TYPE
		SYNTAX  CounterBasedGauge64 
		MAX-ACCESS read-only 
		STATUS current
		DESCRIPTION  "Failed in SSL handshakes" 
		::={ acosSlbSslForwardProxyS 10 } 

		failedInCryptoOperations OBJECT-TYPE
		SYNTAX  CounterBasedGauge64 
		MAX-ACCESS read-only 
		STATUS current
		DESCRIPTION  "Failed in crypto operations" 
		::={ acosSlbSslForwardProxyS 11 } 

		failedInTcp OBJECT-TYPE
		SYNTAX  CounterBasedGauge64 
		MAX-ACCESS read-only 
		STATUS current
		DESCRIPTION  "Failed in TCP" 
		::={ acosSlbSslForwardProxyS 12 } 

		failedInCertificateVerification OBJECT-TYPE
		SYNTAX  CounterBasedGauge64 
		MAX-ACCESS read-only 
		STATUS current
		DESCRIPTION  "Failed in Certificate verification" 
		::={ acosSlbSslForwardProxyS 13 } 

		failedInCertificateSigning OBJECT-TYPE
		SYNTAX  CounterBasedGauge64 
		MAX-ACCESS read-only 
		STATUS current
		DESCRIPTION  "Failed in Certificate signing" 
		::={ acosSlbSslForwardProxyS 14 } 

		invalidOcspStaplingResponse OBJECT-TYPE
		SYNTAX  CounterBasedGauge64 
		MAX-ACCESS read-only 
		STATUS current
		DESCRIPTION  "Invalid OCSP Stapling Response" 
		::={ acosSlbSslForwardProxyS 15 } 

		revokedOcspResponse OBJECT-TYPE
		SYNTAX  CounterBasedGauge64 
		MAX-ACCESS read-only 
		STATUS current
		DESCRIPTION  "Revoked OCSP Response" 
		::={ acosSlbSslForwardProxyS 16 } 

		unsupportedSslVersion OBJECT-TYPE
		SYNTAX  CounterBasedGauge64 
		MAX-ACCESS read-only 
		STATUS current
		DESCRIPTION  "Unsupported SSL version" 
		::={ acosSlbSslForwardProxyS 17 } 

		certificatesInCache OBJECT-TYPE
		SYNTAX  CounterBasedGauge64 
		MAX-ACCESS read-only 
		STATUS current
		DESCRIPTION  "Certificates in cache" 
		::={ acosSlbSslForwardProxyS 18 } 

		connectionsFailed OBJECT-TYPE
		SYNTAX  CounterBasedGauge64 
		MAX-ACCESS read-only 
		STATUS current
		DESCRIPTION  "Connections failed" 
		::={ acosSlbSslForwardProxyS 19 } 

		aflexBypass OBJECT-TYPE
		SYNTAX  CounterBasedGauge64 
		MAX-ACCESS read-only 
		STATUS current
		DESCRIPTION  "Bypass triggered by aFleX" 
		::={ acosSlbSslForwardProxyS 20 } 

		bypassCertSubjectSessions OBJECT-TYPE
		SYNTAX  CounterBasedGauge64 
		MAX-ACCESS read-only 
		STATUS current
		DESCRIPTION  "Bypass Cert Subject sessions" 
		::={ acosSlbSslForwardProxyS 21 } 

		bypassCertIssuerSessions OBJECT-TYPE
		SYNTAX  CounterBasedGauge64 
		MAX-ACCESS read-only 
		STATUS current
		DESCRIPTION  "Bypass Cert issuer sessions" 
		::={ acosSlbSslForwardProxyS 22 } 

		bypassCertSanSessions OBJECT-TYPE
		SYNTAX  CounterBasedGauge64 
		MAX-ACCESS read-only 
		STATUS current
		DESCRIPTION  "Bypass Cert SAN sessions" 
		::={ acosSlbSslForwardProxyS 23 } 

		bypassNoSniSessions OBJECT-TYPE
		SYNTAX  CounterBasedGauge64 
		MAX-ACCESS read-only 
		STATUS current
		DESCRIPTION  "Bypass NO SNI sessions" 
		::={ acosSlbSslForwardProxyS 24 } 

		resetNoSniSessions OBJECT-TYPE
		SYNTAX  CounterBasedGauge64 
		MAX-ACCESS read-only 
		STATUS current
		DESCRIPTION  "Reset No SNI sessions" 
		::={ acosSlbSslForwardProxyS 25 } 

		bypassEsniSessions OBJECT-TYPE
		SYNTAX  CounterBasedGauge64 
		MAX-ACCESS read-only 
		STATUS current
		DESCRIPTION  "Bypass ESNI sessions" 
		::={ acosSlbSslForwardProxyS 26 } 

		dropEsniSessions OBJECT-TYPE
		SYNTAX  CounterBasedGauge64 
		MAX-ACCESS read-only 
		STATUS current
		DESCRIPTION  "Drop ESNI sessions" 
		::={ acosSlbSslForwardProxyS 27 } 

		bypassUsernameSessions OBJECT-TYPE
		SYNTAX  CounterBasedGauge64 
		MAX-ACCESS read-only 
		STATUS current
		DESCRIPTION  "Bypass Username sessions" 
		::={ acosSlbSslForwardProxyS 28 } 

		bypassAdGroupSessions OBJECT-TYPE
		SYNTAX  CounterBasedGauge64 
		MAX-ACCESS read-only 
		STATUS current
		DESCRIPTION  "Bypass AD-group sessions" 
		::={ acosSlbSslForwardProxyS 29 } 

		totConnInBuff OBJECT-TYPE
		SYNTAX  CounterBasedGauge64 
		MAX-ACCESS read-only 
		STATUS current
		DESCRIPTION  "Total buffered async connections" 
		::={ acosSlbSslForwardProxyS 30 } 

		currConnInBuff OBJECT-TYPE
		SYNTAX  CounterBasedGauge64 
		MAX-ACCESS read-only 
		STATUS current
		DESCRIPTION  "Current buffered async connections" 
		::={ acosSlbSslForwardProxyS 31 } 

		asyncConnTimeout OBJECT-TYPE
		SYNTAX  CounterBasedGauge64 
		MAX-ACCESS read-only 
		STATUS current
		DESCRIPTION  "SSLi Async connections failures due to timeout" 
		::={ acosSlbSslForwardProxyS 32 } 

		asyncConnLimitDrop OBJECT-TYPE
		SYNTAX  CounterBasedGauge64 
		MAX-ACCESS read-only 
		STATUS current
		DESCRIPTION  "SSLi Async connections failures due to limit" 
		::={ acosSlbSslForwardProxyS 33 } 

		certInCache OBJECT-TYPE
		SYNTAX  CounterBasedGauge64 
		MAX-ACCESS read-only 
		STATUS current
		DESCRIPTION  "Certificates in cache used by HC SSLi App" 
		::={ acosSlbSslForwardProxyS 34 } 

		bypassClientIpSessions OBJECT-TYPE
		SYNTAX  CounterBasedGauge64 
		MAX-ACCESS read-only 
		STATUS current
		DESCRIPTION  "Bypass Client IP sessions" 
		::={ acosSlbSslForwardProxyS 35 } 

		bypassServerIpSessions OBJECT-TYPE
		SYNTAX  CounterBasedGauge64 
		MAX-ACCESS read-only 
		STATUS current
		DESCRIPTION  "Bypass Server IP sessions" 
		::={ acosSlbSslForwardProxyS 36 } 

acosSlbSecureGaming                 OBJECT IDENTIFIER ::= { acosSlb 92 }
acosSlbSecureGamingS                OBJECT IDENTIFIER ::= { acosSlbSecureGaming 1 }

		secureGamingPass OBJECT-TYPE
		SYNTAX  CounterBasedGauge64 
		MAX-ACCESS read-only 
		STATUS current
		DESCRIPTION  "Secure Gaming passed" 
		::={ acosSlbSecureGamingS 1 } 

		secureGamingDrop OBJECT-TYPE
		SYNTAX  CounterBasedGauge64 
		MAX-ACCESS read-only 
		STATUS current
		DESCRIPTION  "Secure Gaming dropped" 
		::={ acosSlbSecureGamingS 2 } 

acosSlbTemplate                     OBJECT IDENTIFIER ::= { acosSlb 18 }
acosSlbTemplateCache                OBJECT IDENTIFIER ::= { acosSlbTemplate 2 }
acosSlbTemplateCacheS               OBJECT IDENTIFIER ::= { acosSlbTemplateCache 1 }

slbTemplateCacheSTable OBJECT-TYPE
		SYNTAX SEQUENCE OF SlbTemplateCacheSEntry
		MAX-ACCESS not-accessible
		STATUS current
		::={ acosSlbTemplateCacheS 1 } 


	slbTemplateCacheSEntry OBJECT-TYPE
		SYNTAX SlbTemplateCacheSEntry
		MAX-ACCESS not-accessible
		STATUS current
		INDEX {
			slbTemplateCache
		}
		::={ slbTemplateCacheSTable 1 } 


	SlbTemplateCacheSEntry ::=
		SEQUENCE {
			slbTemplateCache DisplayString, 
			slbTemplateCacheHits CounterBasedGauge64,
			slbTemplateCacheMiss CounterBasedGauge64,
			slbTemplateCacheBytesServed CounterBasedGauge64,
			slbTemplateCacheTotalReq CounterBasedGauge64,
			slbTemplateCacheCachingReq CounterBasedGauge64,
			ncReqHeader CounterBasedGauge64,
			ncResHeader CounterBasedGauge64,
			slbTemplateCacheRvSuccess CounterBasedGauge64,
			rvFailure CounterBasedGauge64,
			slbTemplateCacheImsRequest CounterBasedGauge64,
			slbTemplateCacheNmResponse CounterBasedGauge64,
			slbTemplateCacheRspTypeCL CounterBasedGauge64,
			slbTemplateCacheRspTypeCE CounterBasedGauge64,
			slbTemplateCacheRspType304 CounterBasedGauge64,
			slbTemplateCacheRspTypeOther CounterBasedGauge64,
			slbTemplateCacheRspNoCompress CounterBasedGauge64,
			slbTemplateCacheRspGzip CounterBasedGauge64,
			slbTemplateCacheRspDeflate CounterBasedGauge64,
			slbTemplateCacheRspOther CounterBasedGauge64,
			slbTemplateCacheNocacheMatch CounterBasedGauge64,
			slbTemplateCacheMatch CounterBasedGauge64,
			slbTemplateCacheInvalidateMatch CounterBasedGauge64,
			contentToobig CounterBasedGauge64,
			contentToosmall CounterBasedGauge64,
			entryCreateFailures CounterBasedGauge64,
			slbTemplateCacheMemSize CounterBasedGauge64,
			slbTemplateCacheEntryNum CounterBasedGauge64,
			slbTemplateCacheReplacedEntry CounterBasedGauge64,
			slbTemplateCacheAgingEntry CounterBasedGauge64,
			slbTemplateCacheCleanedEntry CounterBasedGauge64,
			slbTemplateCacheRspTypeStream CounterBasedGauge64,
			slbTemplateCacheHeaderSaveError CounterBasedGauge64,
			slbTemplateCacheRspBr CounterBasedGauge64
		}

			slbTemplateCache OBJECT-TYPE
			SYNTAX  DisplayString 
			MAX-ACCESS read-only 
			STATUS current
			DESCRIPTION  "Specify cache template name" 
			::={ slbTemplateCacheSEntry 1 } 

			slbTemplateCacheHits OBJECT-TYPE
			SYNTAX  CounterBasedGauge64 
			MAX-ACCESS read-only 
			STATUS current
			DESCRIPTION  "Cache hits" 
			::={ slbTemplateCacheSEntry 2 } 

			slbTemplateCacheMiss OBJECT-TYPE
			SYNTAX  CounterBasedGauge64 
			MAX-ACCESS read-only 
			STATUS current
			DESCRIPTION  "Cache misses" 
			::={ slbTemplateCacheSEntry 3 } 

			slbTemplateCacheBytesServed OBJECT-TYPE
			SYNTAX  CounterBasedGauge64 
			MAX-ACCESS read-only 
			STATUS current
			DESCRIPTION  "Bytes served from cache" 
			::={ slbTemplateCacheSEntry 4 } 

			slbTemplateCacheTotalReq OBJECT-TYPE
			SYNTAX  CounterBasedGauge64 
			MAX-ACCESS read-only 
			STATUS current
			DESCRIPTION  "Total requests received" 
			::={ slbTemplateCacheSEntry 5 } 

			slbTemplateCacheCachingReq OBJECT-TYPE
			SYNTAX  CounterBasedGauge64 
			MAX-ACCESS read-only 
			STATUS current
			DESCRIPTION  "Total requests to cache" 
			::={ slbTemplateCacheSEntry 6 } 

			ncReqHeader OBJECT-TYPE
			SYNTAX  CounterBasedGauge64 
			MAX-ACCESS read-only 
			STATUS current
			DESCRIPTION  "slbTemplateCacheNcReqHeader, help nc_req_header" 
			::={ slbTemplateCacheSEntry 7 } 

			ncResHeader OBJECT-TYPE
			SYNTAX  CounterBasedGauge64 
			MAX-ACCESS read-only 
			STATUS current
			DESCRIPTION  "slbTemplateCacheNcResHeader, help nc_res_header" 
			::={ slbTemplateCacheSEntry 8 } 

			slbTemplateCacheRvSuccess OBJECT-TYPE
			SYNTAX  CounterBasedGauge64 
			MAX-ACCESS read-only 
			STATUS current
			DESCRIPTION  "" 
			::={ slbTemplateCacheSEntry 9 } 

			rvFailure OBJECT-TYPE
			SYNTAX  CounterBasedGauge64 
			MAX-ACCESS read-only 
			STATUS current
			DESCRIPTION  "slbTemplateCacheRvFailure, help rv_failure" 
			::={ slbTemplateCacheSEntry 10 } 

			slbTemplateCacheImsRequest OBJECT-TYPE
			SYNTAX  CounterBasedGauge64 
			MAX-ACCESS read-only 
			STATUS current
			DESCRIPTION  "" 
			::={ slbTemplateCacheSEntry 11 } 

			slbTemplateCacheNmResponse OBJECT-TYPE
			SYNTAX  CounterBasedGauge64 
			MAX-ACCESS read-only 
			STATUS current
			DESCRIPTION  "" 
			::={ slbTemplateCacheSEntry 12 } 

			slbTemplateCacheRspTypeCL OBJECT-TYPE
			SYNTAX  CounterBasedGauge64 
			MAX-ACCESS read-only 
			STATUS current
			DESCRIPTION  "" 
			::={ slbTemplateCacheSEntry 13 } 

			slbTemplateCacheRspTypeCE OBJECT-TYPE
			SYNTAX  CounterBasedGauge64 
			MAX-ACCESS read-only 
			STATUS current
			DESCRIPTION  "" 
			::={ slbTemplateCacheSEntry 14 } 

			slbTemplateCacheRspType304 OBJECT-TYPE
			SYNTAX  CounterBasedGauge64 
			MAX-ACCESS read-only 
			STATUS current
			DESCRIPTION  "" 
			::={ slbTemplateCacheSEntry 15 } 

			slbTemplateCacheRspTypeOther OBJECT-TYPE
			SYNTAX  CounterBasedGauge64 
			MAX-ACCESS read-only 
			STATUS current
			DESCRIPTION  "" 
			::={ slbTemplateCacheSEntry 16 } 

			slbTemplateCacheRspNoCompress OBJECT-TYPE
			SYNTAX  CounterBasedGauge64 
			MAX-ACCESS read-only 
			STATUS current
			DESCRIPTION  "" 
			::={ slbTemplateCacheSEntry 17 } 

			slbTemplateCacheRspGzip OBJECT-TYPE
			SYNTAX  CounterBasedGauge64 
			MAX-ACCESS read-only 
			STATUS current
			DESCRIPTION  "" 
			::={ slbTemplateCacheSEntry 18 } 

			slbTemplateCacheRspDeflate OBJECT-TYPE
			SYNTAX  CounterBasedGauge64 
			MAX-ACCESS read-only 
			STATUS current
			DESCRIPTION  "" 
			::={ slbTemplateCacheSEntry 19 } 

			slbTemplateCacheRspOther OBJECT-TYPE
			SYNTAX  CounterBasedGauge64 
			MAX-ACCESS read-only 
			STATUS current
			DESCRIPTION  "" 
			::={ slbTemplateCacheSEntry 20 } 

			slbTemplateCacheNocacheMatch OBJECT-TYPE
			SYNTAX  CounterBasedGauge64 
			MAX-ACCESS read-only 
			STATUS current
			DESCRIPTION  "" 
			::={ slbTemplateCacheSEntry 21 } 

			slbTemplateCacheMatch OBJECT-TYPE
			SYNTAX  CounterBasedGauge64 
			MAX-ACCESS read-only 
			STATUS current
			DESCRIPTION  "" 
			::={ slbTemplateCacheSEntry 22 } 

			slbTemplateCacheInvalidateMatch OBJECT-TYPE
			SYNTAX  CounterBasedGauge64 
			MAX-ACCESS read-only 
			STATUS current
			DESCRIPTION  "" 
			::={ slbTemplateCacheSEntry 23 } 

			contentToobig OBJECT-TYPE
			SYNTAX  CounterBasedGauge64 
			MAX-ACCESS read-only 
			STATUS current
			DESCRIPTION  "slbTemplateCacheContentToobig, help content_toobig" 
			::={ slbTemplateCacheSEntry 24 } 

			contentToosmall OBJECT-TYPE
			SYNTAX  CounterBasedGauge64 
			MAX-ACCESS read-only 
			STATUS current
			DESCRIPTION  "slbTemplateCacheContentToosmall, help content_toosmall" 
			::={ slbTemplateCacheSEntry 25 } 

			entryCreateFailures OBJECT-TYPE
			SYNTAX  CounterBasedGauge64 
			MAX-ACCESS read-only 
			STATUS current
			DESCRIPTION  "slbTemplateCacheEntryCreateFailures, help entry_create_failures" 
			::={ slbTemplateCacheSEntry 26 } 

			slbTemplateCacheMemSize OBJECT-TYPE
			SYNTAX  CounterBasedGauge64 
			MAX-ACCESS read-only 
			STATUS current
			DESCRIPTION  "" 
			::={ slbTemplateCacheSEntry 27 } 

			slbTemplateCacheEntryNum OBJECT-TYPE
			SYNTAX  CounterBasedGauge64 
			MAX-ACCESS read-only 
			STATUS current
			DESCRIPTION  "" 
			::={ slbTemplateCacheSEntry 28 } 

			slbTemplateCacheReplacedEntry OBJECT-TYPE
			SYNTAX  CounterBasedGauge64 
			MAX-ACCESS read-only 
			STATUS current
			DESCRIPTION  "" 
			::={ slbTemplateCacheSEntry 29 } 

			slbTemplateCacheAgingEntry OBJECT-TYPE
			SYNTAX  CounterBasedGauge64 
			MAX-ACCESS read-only 
			STATUS current
			DESCRIPTION  "" 
			::={ slbTemplateCacheSEntry 30 } 

			slbTemplateCacheCleanedEntry OBJECT-TYPE
			SYNTAX  CounterBasedGauge64 
			MAX-ACCESS read-only 
			STATUS current
			DESCRIPTION  "" 
			::={ slbTemplateCacheSEntry 31 } 

			slbTemplateCacheRspTypeStream OBJECT-TYPE
			SYNTAX  CounterBasedGauge64 
			MAX-ACCESS read-only 
			STATUS current
			DESCRIPTION  "" 
			::={ slbTemplateCacheSEntry 32 } 

			slbTemplateCacheHeaderSaveError OBJECT-TYPE
			SYNTAX  CounterBasedGauge64 
			MAX-ACCESS read-only 
			STATUS current
			DESCRIPTION  "" 
			::={ slbTemplateCacheSEntry 33 } 

			slbTemplateCacheRspBr OBJECT-TYPE
			SYNTAX  CounterBasedGauge64 
			MAX-ACCESS read-only 
			STATUS current
			DESCRIPTION  "" 
			::={ slbTemplateCacheSEntry 34 } 

acosSlbTemplateClientSsl            OBJECT IDENTIFIER ::= { acosSlbTemplate 4 }
acosSlbTemplateClientSslS           OBJECT IDENTIFIER ::= { acosSlbTemplateClientSsl 1 }

slbTemplateClientSslSTable OBJECT-TYPE
		SYNTAX SEQUENCE OF SlbTemplateClientSslSEntry
		MAX-ACCESS not-accessible
		STATUS current
		::={ acosSlbTemplateClientSslS 1 } 


	slbTemplateClientSslSEntry OBJECT-TYPE
		SYNTAX SlbTemplateClientSslSEntry
		MAX-ACCESS not-accessible
		STATUS current
		INDEX {
			slbTemplateClientSslName
		}
		::={ slbTemplateClientSslSTable 1 } 


	SlbTemplateClientSslSEntry ::=
		SEQUENCE {
			slbTemplateClientSslName DisplayString, 
			realEstate CounterBasedGauge64,
			computerAndInternetSecurity CounterBasedGauge64,
			financialServices CounterBasedGauge64,
			businessAndEconomy CounterBasedGauge64,
			computerAndInternetInfo CounterBasedGauge64,
			auctions CounterBasedGauge64,
			shopping CounterBasedGauge64,
			cultAndOccult CounterBasedGauge64,
			travel CounterBasedGauge64,
			drugs CounterBasedGauge64,
			adultAndPornography CounterBasedGauge64,
			homeAndGarden CounterBasedGauge64,
			military CounterBasedGauge64,
			socialNetwork CounterBasedGauge64,
			deadSites CounterBasedGauge64,
			stockAdviceAndTools CounterBasedGauge64,
			trainingAndTools CounterBasedGauge64,
			dating CounterBasedGauge64,
			sexEducation CounterBasedGauge64,
			religion CounterBasedGauge64,
			entertainmentAndArts CounterBasedGauge64,
			personalSitesAndBlogs CounterBasedGauge64,
			legal CounterBasedGauge64,
			localInformation CounterBasedGauge64,
			streamingMedia CounterBasedGauge64,
			jobSearch CounterBasedGauge64,
			gambling CounterBasedGauge64,
			translation CounterBasedGauge64,
			referenceAndResearch CounterBasedGauge64,
			sharewareAndFreeware CounterBasedGauge64,
			peerToPeer CounterBasedGauge64,
			marijuana CounterBasedGauge64,
			hacking CounterBasedGauge64,
			games CounterBasedGauge64,
			philosophyAndPolitics CounterBasedGauge64,
			weapons CounterBasedGauge64,
			payToSurf CounterBasedGauge64,
			huntingAndFishing CounterBasedGauge64,
			society CounterBasedGauge64,
			educationalInstitutions CounterBasedGauge64,
			onlineGreetingCards CounterBasedGauge64,
			sports CounterBasedGauge64,
			swimsuitsAndIntimateApparel CounterBasedGauge64,
			questionable CounterBasedGauge64,
			kids CounterBasedGauge64,
			hateAndRacism CounterBasedGauge64,
			personalStorage CounterBasedGauge64,
			violence CounterBasedGauge64,
			keyloggersAndMonitoring CounterBasedGauge64,
			searchEngines CounterBasedGauge64,
			internetPortals CounterBasedGauge64,
			webAdvertisements CounterBasedGauge64,
			cheating CounterBasedGauge64,
			gross CounterBasedGauge64,
			webBasedEmail CounterBasedGauge64,
			malwareSites CounterBasedGauge64,
			phishingAndOtherFraud CounterBasedGauge64,
			proxyAvoidAndAnonymizers CounterBasedGauge64,
			spywareAndAdware CounterBasedGauge64,
			music CounterBasedGauge64,
			government CounterBasedGauge64,
			nudity CounterBasedGauge64,
			newsAndMedia CounterBasedGauge64,
			illegal CounterBasedGauge64,
			cdnHits CounterBasedGauge64,
			internetCommunications CounterBasedGauge64,
			botNets CounterBasedGauge64,
			abortion CounterBasedGauge64,
			healthAndMedicine CounterBasedGauge64,
			confirmedSPAMSources CounterBasedGauge64,
			spamUrlHits CounterBasedGauge64,
			unconfirmedSPAMSources CounterBasedGauge64,
			openHTTPProxies CounterBasedGauge64,
			dynamicallyGeneratedContent CounterBasedGauge64,
			parkedDomains CounterBasedGauge64,
			alcoholAndTobacco CounterBasedGauge64,
			privateIPAddresses CounterBasedGauge64,
			imageAndVideoSearch CounterBasedGauge64,
			fashionAndBeauty CounterBasedGauge64,
			recreationAndHobbies CounterBasedGauge64,
			motorVehicles CounterBasedGauge64,
			webHostingSites CounterBasedGauge64,
			foodAndDining CounterBasedGauge64,
			dummyItem CounterBasedGauge64,
			selfHarm CounterBasedGauge64,
			dnsOverHttps CounterBasedGauge64,
			lowThcCannabisProducts CounterBasedGauge64,
			generativeAi CounterBasedGauge64,
			nudityArtistic CounterBasedGauge64,
			illegalPornography CounterBasedGauge64,
			uncategorised CounterBasedGauge64,
			otherCategory CounterBasedGauge64,
			trustworthy CounterBasedGauge64,
			lowRisk CounterBasedGauge64,
			moderateRisk CounterBasedGauge64,
			suspicious CounterBasedGauge64,
			malicious CounterBasedGauge64
		}

			slbTemplateClientSslName OBJECT-TYPE
			SYNTAX  DisplayString 
			MAX-ACCESS read-only 
			STATUS current
			DESCRIPTION  "Client SSL Template Name" 
			::={ slbTemplateClientSslSEntry 1 } 

			realEstate OBJECT-TYPE
			SYNTAX  CounterBasedGauge64 
			MAX-ACCESS read-only 
			STATUS current
			DESCRIPTION  "real estate category" 
			::={ slbTemplateClientSslSEntry 2 } 

			computerAndInternetSecurity OBJECT-TYPE
			SYNTAX  CounterBasedGauge64 
			MAX-ACCESS read-only 
			STATUS current
			DESCRIPTION  "computer and internet security category" 
			::={ slbTemplateClientSslSEntry 3 } 

			financialServices OBJECT-TYPE
			SYNTAX  CounterBasedGauge64 
			MAX-ACCESS read-only 
			STATUS current
			DESCRIPTION  "financial services category" 
			::={ slbTemplateClientSslSEntry 4 } 

			businessAndEconomy OBJECT-TYPE
			SYNTAX  CounterBasedGauge64 
			MAX-ACCESS read-only 
			STATUS current
			DESCRIPTION  "business and economy category" 
			::={ slbTemplateClientSslSEntry 5 } 

			computerAndInternetInfo OBJECT-TYPE
			SYNTAX  CounterBasedGauge64 
			MAX-ACCESS read-only 
			STATUS current
			DESCRIPTION  "computer and internet info category" 
			::={ slbTemplateClientSslSEntry 6 } 

			auctions OBJECT-TYPE
			SYNTAX  CounterBasedGauge64 
			MAX-ACCESS read-only 
			STATUS current
			DESCRIPTION  "auctions category" 
			::={ slbTemplateClientSslSEntry 7 } 

			shopping OBJECT-TYPE
			SYNTAX  CounterBasedGauge64 
			MAX-ACCESS read-only 
			STATUS current
			DESCRIPTION  "shopping category" 
			::={ slbTemplateClientSslSEntry 8 } 

			cultAndOccult OBJECT-TYPE
			SYNTAX  CounterBasedGauge64 
			MAX-ACCESS read-only 
			STATUS current
			DESCRIPTION  "cult and occult category" 
			::={ slbTemplateClientSslSEntry 9 } 

			travel OBJECT-TYPE
			SYNTAX  CounterBasedGauge64 
			MAX-ACCESS read-only 
			STATUS current
			DESCRIPTION  "travel category" 
			::={ slbTemplateClientSslSEntry 10 } 

			drugs OBJECT-TYPE
			SYNTAX  CounterBasedGauge64 
			MAX-ACCESS read-only 
			STATUS current
			DESCRIPTION  "drugs category" 
			::={ slbTemplateClientSslSEntry 11 } 

			adultAndPornography OBJECT-TYPE
			SYNTAX  CounterBasedGauge64 
			MAX-ACCESS read-only 
			STATUS current
			DESCRIPTION  "adult and pornography category" 
			::={ slbTemplateClientSslSEntry 12 } 

			homeAndGarden OBJECT-TYPE
			SYNTAX  CounterBasedGauge64 
			MAX-ACCESS read-only 
			STATUS current
			DESCRIPTION  "home and garden category" 
			::={ slbTemplateClientSslSEntry 13 } 

			military OBJECT-TYPE
			SYNTAX  CounterBasedGauge64 
			MAX-ACCESS read-only 
			STATUS current
			DESCRIPTION  "military category" 
			::={ slbTemplateClientSslSEntry 14 } 

			socialNetwork OBJECT-TYPE
			SYNTAX  CounterBasedGauge64 
			MAX-ACCESS read-only 
			STATUS current
			DESCRIPTION  "social network category" 
			::={ slbTemplateClientSslSEntry 15 } 

			deadSites OBJECT-TYPE
			SYNTAX  CounterBasedGauge64 
			MAX-ACCESS read-only 
			STATUS current
			DESCRIPTION  "dead sites category" 
			::={ slbTemplateClientSslSEntry 16 } 

			stockAdviceAndTools OBJECT-TYPE
			SYNTAX  CounterBasedGauge64 
			MAX-ACCESS read-only 
			STATUS current
			DESCRIPTION  "stock advice and tools category" 
			::={ slbTemplateClientSslSEntry 17 } 

			trainingAndTools OBJECT-TYPE
			SYNTAX  CounterBasedGauge64 
			MAX-ACCESS read-only 
			STATUS current
			DESCRIPTION  "training and tools category" 
			::={ slbTemplateClientSslSEntry 18 } 

			dating OBJECT-TYPE
			SYNTAX  CounterBasedGauge64 
			MAX-ACCESS read-only 
			STATUS current
			DESCRIPTION  "dating category" 
			::={ slbTemplateClientSslSEntry 19 } 

			sexEducation OBJECT-TYPE
			SYNTAX  CounterBasedGauge64 
			MAX-ACCESS read-only 
			STATUS current
			DESCRIPTION  "sex education category" 
			::={ slbTemplateClientSslSEntry 20 } 

			religion OBJECT-TYPE
			SYNTAX  CounterBasedGauge64 
			MAX-ACCESS read-only 
			STATUS current
			DESCRIPTION  "religion category" 
			::={ slbTemplateClientSslSEntry 21 } 

			entertainmentAndArts OBJECT-TYPE
			SYNTAX  CounterBasedGauge64 
			MAX-ACCESS read-only 
			STATUS current
			DESCRIPTION  "entertainment and arts category" 
			::={ slbTemplateClientSslSEntry 22 } 

			personalSitesAndBlogs OBJECT-TYPE
			SYNTAX  CounterBasedGauge64 
			MAX-ACCESS read-only 
			STATUS current
			DESCRIPTION  "personal sites and blogs category" 
			::={ slbTemplateClientSslSEntry 23 } 

			legal OBJECT-TYPE
			SYNTAX  CounterBasedGauge64 
			MAX-ACCESS read-only 
			STATUS current
			DESCRIPTION  "legal category" 
			::={ slbTemplateClientSslSEntry 24 } 

			localInformation OBJECT-TYPE
			SYNTAX  CounterBasedGauge64 
			MAX-ACCESS read-only 
			STATUS current
			DESCRIPTION  "local information category" 
			::={ slbTemplateClientSslSEntry 25 } 

			streamingMedia OBJECT-TYPE
			SYNTAX  CounterBasedGauge64 
			MAX-ACCESS read-only 
			STATUS current
			DESCRIPTION  "streaming media category" 
			::={ slbTemplateClientSslSEntry 26 } 

			jobSearch OBJECT-TYPE
			SYNTAX  CounterBasedGauge64 
			MAX-ACCESS read-only 
			STATUS current
			DESCRIPTION  "job search category" 
			::={ slbTemplateClientSslSEntry 27 } 

			gambling OBJECT-TYPE
			SYNTAX  CounterBasedGauge64 
			MAX-ACCESS read-only 
			STATUS current
			DESCRIPTION  "gambling category" 
			::={ slbTemplateClientSslSEntry 28 } 

			translation OBJECT-TYPE
			SYNTAX  CounterBasedGauge64 
			MAX-ACCESS read-only 
			STATUS current
			DESCRIPTION  "translation category" 
			::={ slbTemplateClientSslSEntry 29 } 

			referenceAndResearch OBJECT-TYPE
			SYNTAX  CounterBasedGauge64 
			MAX-ACCESS read-only 
			STATUS current
			DESCRIPTION  "reference and research category" 
			::={ slbTemplateClientSslSEntry 30 } 

			sharewareAndFreeware OBJECT-TYPE
			SYNTAX  CounterBasedGauge64 
			MAX-ACCESS read-only 
			STATUS current
			DESCRIPTION  "shareware and freeware category" 
			::={ slbTemplateClientSslSEntry 31 } 

			peerToPeer OBJECT-TYPE
			SYNTAX  CounterBasedGauge64 
			MAX-ACCESS read-only 
			STATUS current
			DESCRIPTION  "peer to peer category" 
			::={ slbTemplateClientSslSEntry 32 } 

			marijuana OBJECT-TYPE
			SYNTAX  CounterBasedGauge64 
			MAX-ACCESS read-only 
			STATUS current
			DESCRIPTION  "marijuana category" 
			::={ slbTemplateClientSslSEntry 33 } 

			hacking OBJECT-TYPE
			SYNTAX  CounterBasedGauge64 
			MAX-ACCESS read-only 
			STATUS current
			DESCRIPTION  "hacking category" 
			::={ slbTemplateClientSslSEntry 34 } 

			games OBJECT-TYPE
			SYNTAX  CounterBasedGauge64 
			MAX-ACCESS read-only 
			STATUS current
			DESCRIPTION  "games category" 
			::={ slbTemplateClientSslSEntry 35 } 

			philosophyAndPolitics OBJECT-TYPE
			SYNTAX  CounterBasedGauge64 
			MAX-ACCESS read-only 
			STATUS current
			DESCRIPTION  "philosophy and politics category" 
			::={ slbTemplateClientSslSEntry 36 } 

			weapons OBJECT-TYPE
			SYNTAX  CounterBasedGauge64 
			MAX-ACCESS read-only 
			STATUS current
			DESCRIPTION  "weapons category" 
			::={ slbTemplateClientSslSEntry 37 } 

			payToSurf OBJECT-TYPE
			SYNTAX  CounterBasedGauge64 
			MAX-ACCESS read-only 
			STATUS current
			DESCRIPTION  "pay to surf category" 
			::={ slbTemplateClientSslSEntry 38 } 

			huntingAndFishing OBJECT-TYPE
			SYNTAX  CounterBasedGauge64 
			MAX-ACCESS read-only 
			STATUS current
			DESCRIPTION  "hunting and fishing category" 
			::={ slbTemplateClientSslSEntry 39 } 

			society OBJECT-TYPE
			SYNTAX  CounterBasedGauge64 
			MAX-ACCESS read-only 
			STATUS current
			DESCRIPTION  "society category" 
			::={ slbTemplateClientSslSEntry 40 } 

			educationalInstitutions OBJECT-TYPE
			SYNTAX  CounterBasedGauge64 
			MAX-ACCESS read-only 
			STATUS current
			DESCRIPTION  "educational institutions category" 
			::={ slbTemplateClientSslSEntry 41 } 

			onlineGreetingCards OBJECT-TYPE
			SYNTAX  CounterBasedGauge64 
			MAX-ACCESS read-only 
			STATUS current
			DESCRIPTION  "online greeting cards category" 
			::={ slbTemplateClientSslSEntry 42 } 

			sports OBJECT-TYPE
			SYNTAX  CounterBasedGauge64 
			MAX-ACCESS read-only 
			STATUS current
			DESCRIPTION  "sports category" 
			::={ slbTemplateClientSslSEntry 43 } 

			swimsuitsAndIntimateApparel OBJECT-TYPE
			SYNTAX  CounterBasedGauge64 
			MAX-ACCESS read-only 
			STATUS current
			DESCRIPTION  "swimsuits and intimate apparel category" 
			::={ slbTemplateClientSslSEntry 44 } 

			questionable OBJECT-TYPE
			SYNTAX  CounterBasedGauge64 
			MAX-ACCESS read-only 
			STATUS current
			DESCRIPTION  "questionable category" 
			::={ slbTemplateClientSslSEntry 45 } 

			kids OBJECT-TYPE
			SYNTAX  CounterBasedGauge64 
			MAX-ACCESS read-only 
			STATUS current
			DESCRIPTION  "kids category" 
			::={ slbTemplateClientSslSEntry 46 } 

			hateAndRacism OBJECT-TYPE
			SYNTAX  CounterBasedGauge64 
			MAX-ACCESS read-only 
			STATUS current
			DESCRIPTION  "hate and racism category" 
			::={ slbTemplateClientSslSEntry 47 } 

			personalStorage OBJECT-TYPE
			SYNTAX  CounterBasedGauge64 
			MAX-ACCESS read-only 
			STATUS current
			DESCRIPTION  "personal storage category" 
			::={ slbTemplateClientSslSEntry 48 } 

			violence OBJECT-TYPE
			SYNTAX  CounterBasedGauge64 
			MAX-ACCESS read-only 
			STATUS current
			DESCRIPTION  "violence category" 
			::={ slbTemplateClientSslSEntry 49 } 

			keyloggersAndMonitoring OBJECT-TYPE
			SYNTAX  CounterBasedGauge64 
			MAX-ACCESS read-only 
			STATUS current
			DESCRIPTION  "keyloggers and monitoring category" 
			::={ slbTemplateClientSslSEntry 50 } 

			searchEngines OBJECT-TYPE
			SYNTAX  CounterBasedGauge64 
			MAX-ACCESS read-only 
			STATUS current
			DESCRIPTION  "search engines category" 
			::={ slbTemplateClientSslSEntry 51 } 

			internetPortals OBJECT-TYPE
			SYNTAX  CounterBasedGauge64 
			MAX-ACCESS read-only 
			STATUS current
			DESCRIPTION  "internet portals category" 
			::={ slbTemplateClientSslSEntry 52 } 

			webAdvertisements OBJECT-TYPE
			SYNTAX  CounterBasedGauge64 
			MAX-ACCESS read-only 
			STATUS current
			DESCRIPTION  "web advertisements category" 
			::={ slbTemplateClientSslSEntry 53 } 

			cheating OBJECT-TYPE
			SYNTAX  CounterBasedGauge64 
			MAX-ACCESS read-only 
			STATUS current
			DESCRIPTION  "cheating category" 
			::={ slbTemplateClientSslSEntry 54 } 

			gross OBJECT-TYPE
			SYNTAX  CounterBasedGauge64 
			MAX-ACCESS read-only 
			STATUS current
			DESCRIPTION  "gross category" 
			::={ slbTemplateClientSslSEntry 55 } 

			webBasedEmail OBJECT-TYPE
			SYNTAX  CounterBasedGauge64 
			MAX-ACCESS read-only 
			STATUS current
			DESCRIPTION  "web based email category" 
			::={ slbTemplateClientSslSEntry 56 } 

			malwareSites OBJECT-TYPE
			SYNTAX  CounterBasedGauge64 
			MAX-ACCESS read-only 
			STATUS current
			DESCRIPTION  "malware sites category" 
			::={ slbTemplateClientSslSEntry 57 } 

			phishingAndOtherFraud OBJECT-TYPE
			SYNTAX  CounterBasedGauge64 
			MAX-ACCESS read-only 
			STATUS current
			DESCRIPTION  "phishing and other fraud category" 
			::={ slbTemplateClientSslSEntry 58 } 

			proxyAvoidAndAnonymizers OBJECT-TYPE
			SYNTAX  CounterBasedGauge64 
			MAX-ACCESS read-only 
			STATUS current
			DESCRIPTION  "proxy avoid and anonymizers category" 
			::={ slbTemplateClientSslSEntry 59 } 

			spywareAndAdware OBJECT-TYPE
			SYNTAX  CounterBasedGauge64 
			MAX-ACCESS read-only 
			STATUS current
			DESCRIPTION  "spyware and adware category" 
			::={ slbTemplateClientSslSEntry 60 } 

			music OBJECT-TYPE
			SYNTAX  CounterBasedGauge64 
			MAX-ACCESS read-only 
			STATUS current
			DESCRIPTION  "music category" 
			::={ slbTemplateClientSslSEntry 61 } 

			government OBJECT-TYPE
			SYNTAX  CounterBasedGauge64 
			MAX-ACCESS read-only 
			STATUS current
			DESCRIPTION  "government category" 
			::={ slbTemplateClientSslSEntry 62 } 

			nudity OBJECT-TYPE
			SYNTAX  CounterBasedGauge64 
			MAX-ACCESS read-only 
			STATUS current
			DESCRIPTION  "nudity category" 
			::={ slbTemplateClientSslSEntry 63 } 

			newsAndMedia OBJECT-TYPE
			SYNTAX  CounterBasedGauge64 
			MAX-ACCESS read-only 
			STATUS current
			DESCRIPTION  "news and media category" 
			::={ slbTemplateClientSslSEntry 64 } 

			illegal OBJECT-TYPE
			SYNTAX  CounterBasedGauge64 
			MAX-ACCESS read-only 
			STATUS current
			DESCRIPTION  "illegal category" 
			::={ slbTemplateClientSslSEntry 65 } 

			cdnHits OBJECT-TYPE
			SYNTAX  CounterBasedGauge64 
			MAX-ACCESS read-only 
			STATUS current
			DESCRIPTION  "content delivery networks category" 
			::={ slbTemplateClientSslSEntry 66 } 

			internetCommunications OBJECT-TYPE
			SYNTAX  CounterBasedGauge64 
			MAX-ACCESS read-only 
			STATUS current
			DESCRIPTION  "internet communications category" 
			::={ slbTemplateClientSslSEntry 67 } 

			botNets OBJECT-TYPE
			SYNTAX  CounterBasedGauge64 
			MAX-ACCESS read-only 
			STATUS current
			DESCRIPTION  "bot nets category" 
			::={ slbTemplateClientSslSEntry 68 } 

			abortion OBJECT-TYPE
			SYNTAX  CounterBasedGauge64 
			MAX-ACCESS read-only 
			STATUS current
			DESCRIPTION  "abortion category" 
			::={ slbTemplateClientSslSEntry 69 } 

			healthAndMedicine OBJECT-TYPE
			SYNTAX  CounterBasedGauge64 
			MAX-ACCESS read-only 
			STATUS current
			DESCRIPTION  "health and medicine category" 
			::={ slbTemplateClientSslSEntry 70 } 

			confirmedSPAMSources OBJECT-TYPE
			SYNTAX  CounterBasedGauge64 
			MAX-ACCESS read-only 
			STATUS current
			DESCRIPTION  "confirmed SPAM sources category" 
			::={ slbTemplateClientSslSEntry 71 } 

			spamUrlHits OBJECT-TYPE
			SYNTAX  CounterBasedGauge64 
			MAX-ACCESS read-only 
			STATUS current
			DESCRIPTION  "SPAM URLs category" 
			::={ slbTemplateClientSslSEntry 72 } 

			unconfirmedSPAMSources OBJECT-TYPE
			SYNTAX  CounterBasedGauge64 
			MAX-ACCESS read-only 
			STATUS current
			DESCRIPTION  "unconfirmed SPAM sources category" 
			::={ slbTemplateClientSslSEntry 73 } 

			openHTTPProxies OBJECT-TYPE
			SYNTAX  CounterBasedGauge64 
			MAX-ACCESS read-only 
			STATUS current
			DESCRIPTION  "open HTTP proxies category" 
			::={ slbTemplateClientSslSEntry 74 } 

			dynamicallyGeneratedContent OBJECT-TYPE
			SYNTAX  CounterBasedGauge64 
			MAX-ACCESS read-only 
			STATUS current
			DESCRIPTION  "dynamically generated content category" 
			::={ slbTemplateClientSslSEntry 75 } 

			parkedDomains OBJECT-TYPE
			SYNTAX  CounterBasedGauge64 
			MAX-ACCESS read-only 
			STATUS current
			DESCRIPTION  "parked domains category" 
			::={ slbTemplateClientSslSEntry 76 } 

			alcoholAndTobacco OBJECT-TYPE
			SYNTAX  CounterBasedGauge64 
			MAX-ACCESS read-only 
			STATUS current
			DESCRIPTION  "alcohol and tobacco category" 
			::={ slbTemplateClientSslSEntry 77 } 

			privateIPAddresses OBJECT-TYPE
			SYNTAX  CounterBasedGauge64 
			MAX-ACCESS read-only 
			STATUS current
			DESCRIPTION  "private IP addresses category" 
			::={ slbTemplateClientSslSEntry 78 } 

			imageAndVideoSearch OBJECT-TYPE
			SYNTAX  CounterBasedGauge64 
			MAX-ACCESS read-only 
			STATUS current
			DESCRIPTION  "image and video search category" 
			::={ slbTemplateClientSslSEntry 79 } 

			fashionAndBeauty OBJECT-TYPE
			SYNTAX  CounterBasedGauge64 
			MAX-ACCESS read-only 
			STATUS current
			DESCRIPTION  "fashion and beauty category" 
			::={ slbTemplateClientSslSEntry 80 } 

			recreationAndHobbies OBJECT-TYPE
			SYNTAX  CounterBasedGauge64 
			MAX-ACCESS read-only 
			STATUS current
			DESCRIPTION  "recreation and hobbies category" 
			::={ slbTemplateClientSslSEntry 81 } 

			motorVehicles OBJECT-TYPE
			SYNTAX  CounterBasedGauge64 
			MAX-ACCESS read-only 
			STATUS current
			DESCRIPTION  "motor vehicles category" 
			::={ slbTemplateClientSslSEntry 82 } 

			webHostingSites OBJECT-TYPE
			SYNTAX  CounterBasedGauge64 
			MAX-ACCESS read-only 
			STATUS current
			DESCRIPTION  "web hosting sites category" 
			::={ slbTemplateClientSslSEntry 83 } 

			foodAndDining OBJECT-TYPE
			SYNTAX  CounterBasedGauge64 
			MAX-ACCESS read-only 
			STATUS current
			DESCRIPTION  "food and dining category" 
			::={ slbTemplateClientSslSEntry 84 } 

			dummyItem OBJECT-TYPE
			SYNTAX  CounterBasedGauge64 
			MAX-ACCESS read-only 
			STATUS current
			DESCRIPTION  "dummy item category" 
			::={ slbTemplateClientSslSEntry 85 } 

			selfHarm OBJECT-TYPE
			SYNTAX  CounterBasedGauge64 
			MAX-ACCESS read-only 
			STATUS current
			DESCRIPTION  "self harm category" 
			::={ slbTemplateClientSslSEntry 86 } 

			dnsOverHttps OBJECT-TYPE
			SYNTAX  CounterBasedGauge64 
			MAX-ACCESS read-only 
			STATUS current
			DESCRIPTION  "dns over https category" 
			::={ slbTemplateClientSslSEntry 87 } 

			lowThcCannabisProducts OBJECT-TYPE
			SYNTAX  CounterBasedGauge64 
			MAX-ACCESS read-only 
			STATUS current
			DESCRIPTION  "low-thc cannabis products" 
			::={ slbTemplateClientSslSEntry 88 } 

			generativeAi OBJECT-TYPE
			SYNTAX  CounterBasedGauge64 
			MAX-ACCESS read-only 
			STATUS current
			DESCRIPTION  "generative ai category" 
			::={ slbTemplateClientSslSEntry 89 } 

			nudityArtistic OBJECT-TYPE
			SYNTAX  CounterBasedGauge64 
			MAX-ACCESS read-only 
			STATUS current
			DESCRIPTION  "artistic nudity" 
			::={ slbTemplateClientSslSEntry 90 } 

			illegalPornography OBJECT-TYPE
			SYNTAX  CounterBasedGauge64 
			MAX-ACCESS read-only 
			STATUS current
			DESCRIPTION  "illegal pornography eg. child sexual abuse" 
			::={ slbTemplateClientSslSEntry 91 } 

			uncategorised OBJECT-TYPE
			SYNTAX  CounterBasedGauge64 
			MAX-ACCESS read-only 
			STATUS current
			DESCRIPTION  "uncategorised" 
			::={ slbTemplateClientSslSEntry 92 } 

			otherCategory OBJECT-TYPE
			SYNTAX  CounterBasedGauge64 
			MAX-ACCESS read-only 
			STATUS current
			DESCRIPTION  "other category" 
			::={ slbTemplateClientSslSEntry 93 } 

			trustworthy OBJECT-TYPE
			SYNTAX  CounterBasedGauge64 
			MAX-ACCESS read-only 
			STATUS current
			DESCRIPTION  "Trustworthy level(81-100)" 
			::={ slbTemplateClientSslSEntry 94 } 

			lowRisk OBJECT-TYPE
			SYNTAX  CounterBasedGauge64 
			MAX-ACCESS read-only 
			STATUS current
			DESCRIPTION  "Low-risk level(61-80)" 
			::={ slbTemplateClientSslSEntry 95 } 

			moderateRisk OBJECT-TYPE
			SYNTAX  CounterBasedGauge64 
			MAX-ACCESS read-only 
			STATUS current
			DESCRIPTION  "Moderate-risk level(41-60)" 
			::={ slbTemplateClientSslSEntry 96 } 

			suspicious OBJECT-TYPE
			SYNTAX  CounterBasedGauge64 
			MAX-ACCESS read-only 
			STATUS current
			DESCRIPTION  "Suspicious level(21-40)" 
			::={ slbTemplateClientSslSEntry 97 } 

			malicious OBJECT-TYPE
			SYNTAX  CounterBasedGauge64 
			MAX-ACCESS read-only 
			STATUS current
			DESCRIPTION  "Malicious level(1-20)" 
			::={ slbTemplateClientSslSEntry 98 } 

acosSlbTemplateClientSsh            OBJECT IDENTIFIER ::= { acosSlbTemplate 5 }
acosSlbTemplateClientSshS           OBJECT IDENTIFIER ::= { acosSlbTemplateClientSsh 1 }

slbTemplateClientSshSTable OBJECT-TYPE
		SYNTAX SEQUENCE OF SlbTemplateClientSshSEntry
		MAX-ACCESS not-accessible
		STATUS current
		::={ acosSlbTemplateClientSshS 1 } 


	slbTemplateClientSshSEntry OBJECT-TYPE
		SYNTAX SlbTemplateClientSshSEntry
		MAX-ACCESS not-accessible
		STATUS current
		INDEX {
			name
		}
		::={ slbTemplateClientSshSTable 1 } 


	SlbTemplateClientSshSEntry ::=
		SEQUENCE {
			name DisplayString, 
			successfulHandshakes CounterBasedGauge64,
			failedHandshakes CounterBasedGauge64,
			forwardingErrors CounterBasedGauge64
		}

			name OBJECT-TYPE
			SYNTAX  DisplayString 
			MAX-ACCESS read-only 
			STATUS current
			DESCRIPTION  "Client SSH Template Name" 
			::={ slbTemplateClientSshSEntry 1 } 

			successfulHandshakes OBJECT-TYPE
			SYNTAX  CounterBasedGauge64 
			MAX-ACCESS read-only 
			STATUS current
			DESCRIPTION  "" 
			::={ slbTemplateClientSshSEntry 2 } 

			failedHandshakes OBJECT-TYPE
			SYNTAX  CounterBasedGauge64 
			MAX-ACCESS read-only 
			STATUS current
			DESCRIPTION  "" 
			::={ slbTemplateClientSshSEntry 3 } 

			forwardingErrors OBJECT-TYPE
			SYNTAX  CounterBasedGauge64 
			MAX-ACCESS read-only 
			STATUS current
			DESCRIPTION  "" 
			::={ slbTemplateClientSshSEntry 4 } 

acosSlbTemplatePolicy               OBJECT IDENTIFIER ::= { acosSlbTemplate 13 }
acosSlbTemplatePolicyS              OBJECT IDENTIFIER ::= { acosSlbTemplatePolicy 1 }

slbTemplatePolicySTable OBJECT-TYPE
		SYNTAX SEQUENCE OF SlbTemplatePolicySEntry
		MAX-ACCESS not-accessible
		STATUS current
		::={ acosSlbTemplatePolicyS 1 } 


	slbTemplatePolicySEntry OBJECT-TYPE
		SYNTAX SlbTemplatePolicySEntry
		MAX-ACCESS not-accessible
		STATUS current
		INDEX {
			name
		}
		::={ slbTemplatePolicySTable 1 } 


	SlbTemplatePolicySEntry ::=
		SEQUENCE {
			name DisplayString, 
			fwdPolicyDnsUnresolved CounterBasedGauge64,
			fwdPolicyDnsOutstanding CounterBasedGauge64,
			fwdPolicySnatFail CounterBasedGauge64,
			fwdPolicyHits CounterBasedGauge64,
			fwdPolicyForwardToInternet CounterBasedGauge64,
			fwdPolicyForwardToServiceGroup CounterBasedGauge64,
			fwdPolicyForwardToProxy CounterBasedGauge64,
			fwdPolicyPolicyDrop CounterBasedGauge64,
			fwdPolicySourceMatchNotFound CounterBasedGauge64,
			expClientHelloNotFound CounterBasedGauge64
		}

			name OBJECT-TYPE
			SYNTAX  DisplayString 
			MAX-ACCESS read-only 
			STATUS current
			DESCRIPTION  "Policy template name" 
			::={ slbTemplatePolicySEntry 1 } 

			fwdPolicyDnsUnresolved OBJECT-TYPE
			SYNTAX  CounterBasedGauge64 
			MAX-ACCESS read-only 
			STATUS current
			DESCRIPTION  "Forward-policy unresolved DNS queries" 
			::={ slbTemplatePolicySEntry 2 } 

			fwdPolicyDnsOutstanding OBJECT-TYPE
			SYNTAX  CounterBasedGauge64 
			MAX-ACCESS read-only 
			STATUS current
			DESCRIPTION  "Forward-policy current DNS outstanding requests" 
			::={ slbTemplatePolicySEntry 3 } 

			fwdPolicySnatFail OBJECT-TYPE
			SYNTAX  CounterBasedGauge64 
			MAX-ACCESS read-only 
			STATUS current
			DESCRIPTION  "Forward-policy source-nat translation failure" 
			::={ slbTemplatePolicySEntry 4 } 

			fwdPolicyHits OBJECT-TYPE
			SYNTAX  CounterBasedGauge64 
			MAX-ACCESS read-only 
			STATUS current
			DESCRIPTION  "Number of forward-policy requests for this policy template" 
			::={ slbTemplatePolicySEntry 5 } 

			fwdPolicyForwardToInternet OBJECT-TYPE
			SYNTAX  CounterBasedGauge64 
			MAX-ACCESS read-only 
			STATUS current
			DESCRIPTION  "Number of forward-policy requests forwarded to internet" 
			::={ slbTemplatePolicySEntry 6 } 

			fwdPolicyForwardToServiceGroup OBJECT-TYPE
			SYNTAX  CounterBasedGauge64 
			MAX-ACCESS read-only 
			STATUS current
			DESCRIPTION  "Number of forward-policy requests forwarded to service group" 
			::={ slbTemplatePolicySEntry 7 } 

			fwdPolicyForwardToProxy OBJECT-TYPE
			SYNTAX  CounterBasedGauge64 
			MAX-ACCESS read-only 
			STATUS current
			DESCRIPTION  "Number of forward-policy requests forwarded to proxy" 
			::={ slbTemplatePolicySEntry 8 } 

			fwdPolicyPolicyDrop OBJECT-TYPE
			SYNTAX  CounterBasedGauge64 
			MAX-ACCESS read-only 
			STATUS current
			DESCRIPTION  "Number of forward-policy requests dropped" 
			::={ slbTemplatePolicySEntry 9 } 

			fwdPolicySourceMatchNotFound OBJECT-TYPE
			SYNTAX  CounterBasedGauge64 
			MAX-ACCESS read-only 
			STATUS current
			DESCRIPTION  "Forward-policy requests without matching source rule" 
			::={ slbTemplatePolicySEntry 10 } 

			expClientHelloNotFound OBJECT-TYPE
			SYNTAX  CounterBasedGauge64 
			MAX-ACCESS read-only 
			STATUS current
			DESCRIPTION  "Expected Client HELLO requests not found" 
			::={ slbTemplatePolicySEntry 11 } 

acosSlbTemplateServerSsh            OBJECT IDENTIFIER ::= { acosSlbTemplate 17 }
acosSlbTemplateServerSshS           OBJECT IDENTIFIER ::= { acosSlbTemplateServerSsh 1 }

slbTemplateServerSshSTable OBJECT-TYPE
		SYNTAX SEQUENCE OF SlbTemplateServerSshSEntry
		MAX-ACCESS not-accessible
		STATUS current
		::={ acosSlbTemplateServerSshS 1 } 


	slbTemplateServerSshSEntry OBJECT-TYPE
		SYNTAX SlbTemplateServerSshSEntry
		MAX-ACCESS not-accessible
		STATUS current
		INDEX {
			name
		}
		::={ slbTemplateServerSshSTable 1 } 


	SlbTemplateServerSshSEntry ::=
		SEQUENCE {
			name DisplayString, 
			successfulHandshakes CounterBasedGauge64,
			failedHandshakes CounterBasedGauge64,
			forwardingErrors CounterBasedGauge64
		}

			name OBJECT-TYPE
			SYNTAX  DisplayString 
			MAX-ACCESS read-only 
			STATUS current
			DESCRIPTION  "Server SSH Template Name" 
			::={ slbTemplateServerSshSEntry 1 } 

			successfulHandshakes OBJECT-TYPE
			SYNTAX  CounterBasedGauge64 
			MAX-ACCESS read-only 
			STATUS current
			DESCRIPTION  "" 
			::={ slbTemplateServerSshSEntry 2 } 

			failedHandshakes OBJECT-TYPE
			SYNTAX  CounterBasedGauge64 
			MAX-ACCESS read-only 
			STATUS current
			DESCRIPTION  "" 
			::={ slbTemplateServerSshSEntry 3 } 

			forwardingErrors OBJECT-TYPE
			SYNTAX  CounterBasedGauge64 
			MAX-ACCESS read-only 
			STATUS current
			DESCRIPTION  "" 
			::={ slbTemplateServerSshSEntry 4 } 

acosSlbTemplateLinkCost             OBJECT IDENTIFIER ::= { acosSlbTemplate 39 }
acosSlbTemplateLinkCostS            OBJECT IDENTIFIER ::= { acosSlbTemplateLinkCost 1 }

slbTemplateLinkCostSTable OBJECT-TYPE
		SYNTAX SEQUENCE OF SlbTemplateLinkCostSEntry
		MAX-ACCESS not-accessible
		STATUS current
		::={ acosSlbTemplateLinkCostS 1 } 


	slbTemplateLinkCostSEntry OBJECT-TYPE
		SYNTAX SlbTemplateLinkCostSEntry
		MAX-ACCESS not-accessible
		STATUS current
		INDEX {
			name
		}
		::={ slbTemplateLinkCostSTable 1 } 


	SlbTemplateLinkCostSEntry ::=
		SEQUENCE {
			name DisplayString, 
			linkTotalFwdBytes CounterBasedGauge64,
			intervalFwdBytes CounterBasedGauge64,
			linkTotalConn CounterBasedGauge64,
			intervalAvgThroughput CounterBasedGauge64,
			intervalMaxThroughput CounterBasedGauge64
		}

			name OBJECT-TYPE
			SYNTAX  DisplayString 
			MAX-ACCESS read-only 
			STATUS current
			DESCRIPTION  "Server Link-Cost Template Name" 
			::={ slbTemplateLinkCostSEntry 1 } 

			linkTotalFwdBytes OBJECT-TYPE
			SYNTAX  CounterBasedGauge64 
			MAX-ACCESS read-only 
			STATUS current
			DESCRIPTION  "Total bytes fwd for link" 
			::={ slbTemplateLinkCostSEntry 2 } 

			intervalFwdBytes OBJECT-TYPE
			SYNTAX  CounterBasedGauge64 
			MAX-ACCESS read-only 
			STATUS current
			DESCRIPTION  "Link Cost bytes processed in forward direction per interval" 
			::={ slbTemplateLinkCostSEntry 3 } 

			linkTotalConn OBJECT-TYPE
			SYNTAX  CounterBasedGauge64 
			MAX-ACCESS read-only 
			STATUS current
			DESCRIPTION  "Link Cost total connection" 
			::={ slbTemplateLinkCostSEntry 4 } 

			intervalAvgThroughput OBJECT-TYPE
			SYNTAX  CounterBasedGauge64 
			MAX-ACCESS read-only 
			STATUS current
			DESCRIPTION  "Link Cost average throughput per interval" 
			::={ slbTemplateLinkCostSEntry 5 } 

			intervalMaxThroughput OBJECT-TYPE
			SYNTAX  CounterBasedGauge64 
			MAX-ACCESS read-only 
			STATUS current
			DESCRIPTION  "Link Cost max throughput per interval" 
			::={ slbTemplateLinkCostSEntry 6 } 

acosSlbServer                       OBJECT IDENTIFIER ::= { acosSlb 21 }
acosSlbServerS                      OBJECT IDENTIFIER ::= { acosSlbServer 1 }

slbServerSTable OBJECT-TYPE
		SYNTAX SEQUENCE OF SlbServerSEntry
		MAX-ACCESS not-accessible
		STATUS current
		::={ acosSlbServerS 1 } 


	slbServerSEntry OBJECT-TYPE
		SYNTAX SlbServerSEntry
		MAX-ACCESS not-accessible
		STATUS current
		INDEX {
			slbServerName
		}
		::={ slbServerSTable 1 } 


	SlbServerSEntry ::=
		SEQUENCE {
			slbServerName DisplayString, 
			slbServerCurrRate CounterBasedGauge64,
			slbServerTotalConn CounterBasedGauge64,
			slbServerFwdPkt CounterBasedGauge64,
			slbServerRevPkt CounterBasedGauge64,
			slbServerPeakConn CounterBasedGauge64,
			totalReq CounterBasedGauge64,
			totalReqSucc CounterBasedGauge64,
			currSslConn CounterBasedGauge64,
			totalSslConn CounterBasedGauge64,
			totalFwdBytes CounterBasedGauge64,
			totalRevBytes CounterBasedGauge64,
			totalFwdPkts CounterBasedGauge64,
			totalRevPkts CounterBasedGauge64,
			ipOnlyLbFwdBytes CounterBasedGauge64,
			ipOnlyLbRevBytes CounterBasedGauge64,
			ipOnlyLbFwdPkts CounterBasedGauge64,
			ipOnlyLbRevPkts CounterBasedGauge64
		}

			slbServerName OBJECT-TYPE
			SYNTAX  DisplayString 
			MAX-ACCESS read-only 
			STATUS current
			DESCRIPTION  "Server Name" 
			::={ slbServerSEntry 1 } 

			slbServerCurrRate OBJECT-TYPE
			SYNTAX  CounterBasedGauge64 
			MAX-ACCESS read-only 
			STATUS current
			DESCRIPTION  "Current established connections" 
			::={ slbServerSEntry 2 } 

			slbServerTotalConn OBJECT-TYPE
			SYNTAX  CounterBasedGauge64 
			MAX-ACCESS read-only 
			STATUS current
			DESCRIPTION  "Total established connections" 
			::={ slbServerSEntry 3 } 

			slbServerFwdPkt OBJECT-TYPE
			SYNTAX  CounterBasedGauge64 
			MAX-ACCESS read-only 
			STATUS current
			DESCRIPTION  "Forward Packets Processed" 
			::={ slbServerSEntry 4 } 

			slbServerRevPkt OBJECT-TYPE
			SYNTAX  CounterBasedGauge64 
			MAX-ACCESS read-only 
			STATUS current
			DESCRIPTION  "Reverse Packets Processed" 
			::={ slbServerSEntry 5 } 

			slbServerPeakConn OBJECT-TYPE
			SYNTAX  CounterBasedGauge64 
			MAX-ACCESS read-only 
			STATUS current
			DESCRIPTION  "Peak number of established connections" 
			::={ slbServerSEntry 6 } 

			totalReq OBJECT-TYPE
			SYNTAX  CounterBasedGauge64 
			MAX-ACCESS read-only 
			STATUS current
			DESCRIPTION  "Total Requests processed" 
			::={ slbServerSEntry 7 } 

			totalReqSucc OBJECT-TYPE
			SYNTAX  CounterBasedGauge64 
			MAX-ACCESS read-only 
			STATUS current
			DESCRIPTION  "Total Requests succeeded" 
			::={ slbServerSEntry 8 } 

			currSslConn OBJECT-TYPE
			SYNTAX  CounterBasedGauge64 
			MAX-ACCESS read-only 
			STATUS current
			DESCRIPTION  "Current SSL connections established" 
			::={ slbServerSEntry 9 } 

			totalSslConn OBJECT-TYPE
			SYNTAX  CounterBasedGauge64 
			MAX-ACCESS read-only 
			STATUS current
			DESCRIPTION  "Total SSL connections established" 
			::={ slbServerSEntry 10 } 

			totalFwdBytes OBJECT-TYPE
			SYNTAX  CounterBasedGauge64 
			MAX-ACCESS read-only 
			STATUS current
			DESCRIPTION  "Bytes processed in forward direction" 
			::={ slbServerSEntry 11 } 

			totalRevBytes OBJECT-TYPE
			SYNTAX  CounterBasedGauge64 
			MAX-ACCESS read-only 
			STATUS current
			DESCRIPTION  "Bytes processed in reverse direction" 
			::={ slbServerSEntry 12 } 

			totalFwdPkts OBJECT-TYPE
			SYNTAX  CounterBasedGauge64 
			MAX-ACCESS read-only 
			STATUS current
			DESCRIPTION  "Packets processed in forward direction" 
			::={ slbServerSEntry 13 } 

			totalRevPkts OBJECT-TYPE
			SYNTAX  CounterBasedGauge64 
			MAX-ACCESS read-only 
			STATUS current
			DESCRIPTION  "Packets processed in reverse direction" 
			::={ slbServerSEntry 14 } 

			ipOnlyLbFwdBytes OBJECT-TYPE
			SYNTAX  CounterBasedGauge64 
			MAX-ACCESS read-only 
			STATUS current
			DESCRIPTION  "IP-Only-LB Bytes processed in forward direction" 
			::={ slbServerSEntry 15 } 

			ipOnlyLbRevBytes OBJECT-TYPE
			SYNTAX  CounterBasedGauge64 
			MAX-ACCESS read-only 
			STATUS current
			DESCRIPTION  "IP-Only-LB Bytes processed in reverse direction" 
			::={ slbServerSEntry 16 } 

			ipOnlyLbFwdPkts OBJECT-TYPE
			SYNTAX  CounterBasedGauge64 
			MAX-ACCESS read-only 
			STATUS current
			DESCRIPTION  "IP-Only-LB Packets processed in forward direction" 
			::={ slbServerSEntry 17 } 

			ipOnlyLbRevPkts OBJECT-TYPE
			SYNTAX  CounterBasedGauge64 
			MAX-ACCESS read-only 
			STATUS current
			DESCRIPTION  "IP-Only-LB Packets processed in reverse direction" 
			::={ slbServerSEntry 18 } 

acosSlbServiceGroup                 OBJECT IDENTIFIER ::= { acosSlb 22 }
acosSlbServiceGroupS                OBJECT IDENTIFIER ::= { acosSlbServiceGroup 1 }

slbServiceGroupSTable OBJECT-TYPE
		SYNTAX SEQUENCE OF SlbServiceGroupSEntry
		MAX-ACCESS not-accessible
		STATUS current
		::={ acosSlbServiceGroupS 1 } 


	slbServiceGroupSEntry OBJECT-TYPE
		SYNTAX SlbServiceGroupSEntry
		MAX-ACCESS not-accessible
		STATUS current
		INDEX {
			slbServiceGroupName
		}
		::={ slbServiceGroupSTable 1 } 


	SlbServiceGroupSEntry ::=
		SEQUENCE {
			slbServiceGroupName DisplayString, 
			serverSelectionFailDrop CounterBasedGauge64,
			serverSelectionFailReset CounterBasedGauge64,
			servicePeakConn CounterBasedGauge64,
			serviceHealthyHost CounterBasedGauge64,
			serviceUnhealthyHost CounterBasedGauge64,
			serviceReqCount CounterBasedGauge64,
			serviceRespCount CounterBasedGauge64,
			serviceResp2xx CounterBasedGauge64,
			serviceResp3xx CounterBasedGauge64,
			serviceResp4xx CounterBasedGauge64,
			serviceResp5xx CounterBasedGauge64,
			serviceCurrConnOverflow CounterBasedGauge64
		}

			slbServiceGroupName OBJECT-TYPE
			SYNTAX  DisplayString 
			MAX-ACCESS read-only 
			STATUS current
			DESCRIPTION  "SLB Service Name" 
			::={ slbServiceGroupSEntry 1 } 

			serverSelectionFailDrop OBJECT-TYPE
			SYNTAX  CounterBasedGauge64 
			MAX-ACCESS read-only 
			STATUS current
			DESCRIPTION  "Drops due to Service selection failure" 
			::={ slbServiceGroupSEntry 2 } 

			serverSelectionFailReset OBJECT-TYPE
			SYNTAX  CounterBasedGauge64 
			MAX-ACCESS read-only 
			STATUS current
			DESCRIPTION  "Resets sent out for Service selection failure" 
			::={ slbServiceGroupSEntry 3 } 

			servicePeakConn OBJECT-TYPE
			SYNTAX  CounterBasedGauge64 
			MAX-ACCESS read-only 
			STATUS current
			DESCRIPTION  "Peak connection count for the Service Group" 
			::={ slbServiceGroupSEntry 4 } 

			serviceHealthyHost OBJECT-TYPE
			SYNTAX  CounterBasedGauge64 
			MAX-ACCESS read-only 
			STATUS current
			DESCRIPTION  "Service Group healthy host count" 
			::={ slbServiceGroupSEntry 5 } 

			serviceUnhealthyHost OBJECT-TYPE
			SYNTAX  CounterBasedGauge64 
			MAX-ACCESS read-only 
			STATUS current
			DESCRIPTION  "Service Group unhealthy host count" 
			::={ slbServiceGroupSEntry 6 } 

			serviceReqCount OBJECT-TYPE
			SYNTAX  CounterBasedGauge64 
			MAX-ACCESS read-only 
			STATUS current
			DESCRIPTION  "Service Group request count" 
			::={ slbServiceGroupSEntry 7 } 

			serviceRespCount OBJECT-TYPE
			SYNTAX  CounterBasedGauge64 
			MAX-ACCESS read-only 
			STATUS current
			DESCRIPTION  "Service Group response count" 
			::={ slbServiceGroupSEntry 8 } 

			serviceResp2xx OBJECT-TYPE
			SYNTAX  CounterBasedGauge64 
			MAX-ACCESS read-only 
			STATUS current
			DESCRIPTION  "Service Group response 2xx count" 
			::={ slbServiceGroupSEntry 9 } 

			serviceResp3xx OBJECT-TYPE
			SYNTAX  CounterBasedGauge64 
			MAX-ACCESS read-only 
			STATUS current
			DESCRIPTION  "Service Group response 3xx count" 
			::={ slbServiceGroupSEntry 10 } 

			serviceResp4xx OBJECT-TYPE
			SYNTAX  CounterBasedGauge64 
			MAX-ACCESS read-only 
			STATUS current
			DESCRIPTION  "Service Group response 4xx count" 
			::={ slbServiceGroupSEntry 11 } 

			serviceResp5xx OBJECT-TYPE
			SYNTAX  CounterBasedGauge64 
			MAX-ACCESS read-only 
			STATUS current
			DESCRIPTION  "Service Group response 5xx count" 
			::={ slbServiceGroupSEntry 12 } 

			serviceCurrConnOverflow OBJECT-TYPE
			SYNTAX  CounterBasedGauge64 
			MAX-ACCESS read-only 
			STATUS current
			DESCRIPTION  "Current connection counter overflow count" 
			::={ slbServiceGroupSEntry 13 } 

acosSlbServiceGroupMember           OBJECT IDENTIFIER ::= { acosSlbServiceGroup 3 }
acosSlbServiceGroupMemberS          OBJECT IDENTIFIER ::= { acosSlbServiceGroupMember 1 }

slbServiceGroupMemberSTable OBJECT-TYPE
		SYNTAX SEQUENCE OF SlbServiceGroupMemberSEntry
		MAX-ACCESS not-accessible
		STATUS current
		::={ acosSlbServiceGroupMemberS 1 } 


	slbServiceGroupMemberSEntry OBJECT-TYPE
		SYNTAX SlbServiceGroupMemberSEntry
		MAX-ACCESS not-accessible
		STATUS current
		INDEX {
			slbServiceGroupName,
			slbServiceGroupMemberName,
			slbServiceGroupMemberPort
		}
		::={ slbServiceGroupMemberSTable 1 } 


	SlbServiceGroupMemberSEntry ::=
		SEQUENCE {
			slbServiceGroupName DisplayString, 
			slbServiceGroupMemberName DisplayString, 
			slbServiceGroupMemberPort INTEGER, 
			currConn CounterBasedGauge64,
			slbServiceGroupMemberTotalFwdBytes CounterBasedGauge64,
			slbServiceGroupMemberTotalFwdPkts CounterBasedGauge64,
			slbServiceGroupMemberTotalRevBytes CounterBasedGauge64,
			slbServiceGroupMemberTotalRevPkts CounterBasedGauge64,
			slbServiceGroupMemberTotalConn CounterBasedGauge64,
			slbServiceGroupMemberTotalRevPktsInspected CounterBasedGauge64,
			slbServiceGroupMemberTotalRevPktsInspectedStatusCode2xx CounterBasedGauge64,
			slbServiceGroupMemberTotalRevPktsInspectedStatusCodeNon5xx CounterBasedGauge64,
			slbServiceGroupMemberCurrReq CounterBasedGauge64,
			slbServiceGroupMemberTotalReq CounterBasedGauge64,
			slbServiceGroupMemberTotalReqSucc CounterBasedGauge64,
			slbServiceGroupMemberPeakConn CounterBasedGauge64,
			slbServiceGroupMemberResponseTime CounterBasedGauge64,
			slbServiceGroupMemberFastestRspTime CounterBasedGauge64,
			slbServiceGroupMemberSlowestRspTime CounterBasedGauge64,
			currSslConn CounterBasedGauge64,
			totalSslConn CounterBasedGauge64,
			currConnOverflow CounterBasedGauge64,
			stateFlaps CounterBasedGauge64
		}

			slbServiceGroupName OBJECT-TYPE
			SYNTAX  DisplayString 
			MAX-ACCESS read-only 
			STATUS current
			DESCRIPTION  "SLB Service Name" 
			::={ slbServiceGroupMemberSEntry 1 } 

			slbServiceGroupMemberName OBJECT-TYPE
			SYNTAX  DisplayString 
			MAX-ACCESS read-only 
			STATUS current
			DESCRIPTION  "Member name" 
			::={ slbServiceGroupMemberSEntry 2 } 

			slbServiceGroupMemberPort OBJECT-TYPE
			SYNTAX  INTEGER 
			MAX-ACCESS read-only 
			STATUS current
			DESCRIPTION  "Port number" 
			::={ slbServiceGroupMemberSEntry 3 } 

			currConn OBJECT-TYPE
			SYNTAX  CounterBasedGauge64 
			MAX-ACCESS read-only 
			STATUS current
			DESCRIPTION  "Current established connections" 
			::={ slbServiceGroupMemberSEntry 4 } 

			slbServiceGroupMemberTotalFwdBytes OBJECT-TYPE
			SYNTAX  CounterBasedGauge64 
			MAX-ACCESS read-only 
			STATUS current
			DESCRIPTION  "Bytes processed in forward direction" 
			::={ slbServiceGroupMemberSEntry 5 } 

			slbServiceGroupMemberTotalFwdPkts OBJECT-TYPE
			SYNTAX  CounterBasedGauge64 
			MAX-ACCESS read-only 
			STATUS current
			DESCRIPTION  "Packets processed in forward direction" 
			::={ slbServiceGroupMemberSEntry 6 } 

			slbServiceGroupMemberTotalRevBytes OBJECT-TYPE
			SYNTAX  CounterBasedGauge64 
			MAX-ACCESS read-only 
			STATUS current
			DESCRIPTION  "Bytes processed in reverse direction" 
			::={ slbServiceGroupMemberSEntry 7 } 

			slbServiceGroupMemberTotalRevPkts OBJECT-TYPE
			SYNTAX  CounterBasedGauge64 
			MAX-ACCESS read-only 
			STATUS current
			DESCRIPTION  "Packets processed in reverse direction" 
			::={ slbServiceGroupMemberSEntry 8 } 

			slbServiceGroupMemberTotalConn OBJECT-TYPE
			SYNTAX  CounterBasedGauge64 
			MAX-ACCESS read-only 
			STATUS current
			DESCRIPTION  "Total established connections" 
			::={ slbServiceGroupMemberSEntry 9 } 

			slbServiceGroupMemberTotalRevPktsInspected OBJECT-TYPE
			SYNTAX  CounterBasedGauge64 
			MAX-ACCESS read-only 
			STATUS current
			DESCRIPTION  "Total reverse packets inspected" 
			::={ slbServiceGroupMemberSEntry 10 } 

			slbServiceGroupMemberTotalRevPktsInspectedStatusCode2xx OBJECT-TYPE
			SYNTAX  CounterBasedGauge64 
			MAX-ACCESS read-only 
			STATUS current
			DESCRIPTION  "Total reverse packets inspected status code 2xx" 
			::={ slbServiceGroupMemberSEntry 11 } 

			slbServiceGroupMemberTotalRevPktsInspectedStatusCodeNon5xx OBJECT-TYPE
			SYNTAX  CounterBasedGauge64 
			MAX-ACCESS read-only 
			STATUS current
			DESCRIPTION  "Total reverse packets inspected status code non 5xx" 
			::={ slbServiceGroupMemberSEntry 12 } 

			slbServiceGroupMemberCurrReq OBJECT-TYPE
			SYNTAX  CounterBasedGauge64 
			MAX-ACCESS read-only 
			STATUS current
			DESCRIPTION  "Current requests" 
			::={ slbServiceGroupMemberSEntry 13 } 

			slbServiceGroupMemberTotalReq OBJECT-TYPE
			SYNTAX  CounterBasedGauge64 
			MAX-ACCESS read-only 
			STATUS current
			DESCRIPTION  "Total requests" 
			::={ slbServiceGroupMemberSEntry 14 } 

			slbServiceGroupMemberTotalReqSucc OBJECT-TYPE
			SYNTAX  CounterBasedGauge64 
			MAX-ACCESS read-only 
			STATUS current
			DESCRIPTION  "Total requests successful" 
			::={ slbServiceGroupMemberSEntry 15 } 

			slbServiceGroupMemberPeakConn OBJECT-TYPE
			SYNTAX  CounterBasedGauge64 
			MAX-ACCESS read-only 
			STATUS current
			DESCRIPTION  "Peak connections" 
			::={ slbServiceGroupMemberSEntry 16 } 

			slbServiceGroupMemberResponseTime OBJECT-TYPE
			SYNTAX  CounterBasedGauge64 
			MAX-ACCESS read-only 
			STATUS current
			DESCRIPTION  "Response time" 
			::={ slbServiceGroupMemberSEntry 17 } 

			slbServiceGroupMemberFastestRspTime OBJECT-TYPE
			SYNTAX  CounterBasedGauge64 
			MAX-ACCESS read-only 
			STATUS current
			DESCRIPTION  "Fastest response time" 
			::={ slbServiceGroupMemberSEntry 18 } 

			slbServiceGroupMemberSlowestRspTime OBJECT-TYPE
			SYNTAX  CounterBasedGauge64 
			MAX-ACCESS read-only 
			STATUS current
			DESCRIPTION  "Slowest response time" 
			::={ slbServiceGroupMemberSEntry 19 } 

			currSslConn OBJECT-TYPE
			SYNTAX  CounterBasedGauge64 
			MAX-ACCESS read-only 
			STATUS current
			DESCRIPTION  "Current SSL connections" 
			::={ slbServiceGroupMemberSEntry 20 } 

			totalSslConn OBJECT-TYPE
			SYNTAX  CounterBasedGauge64 
			MAX-ACCESS read-only 
			STATUS current
			DESCRIPTION  "Total SSL connections" 
			::={ slbServiceGroupMemberSEntry 21 } 

			currConnOverflow OBJECT-TYPE
			SYNTAX  CounterBasedGauge64 
			MAX-ACCESS read-only 
			STATUS current
			DESCRIPTION  "Current connection counter overflow count" 
			::={ slbServiceGroupMemberSEntry 22 } 

			stateFlaps OBJECT-TYPE
			SYNTAX  CounterBasedGauge64 
			MAX-ACCESS read-only 
			STATUS current
			DESCRIPTION  "State flaps count" 
			::={ slbServiceGroupMemberSEntry 23 } 

acosSlbServerGroup                  OBJECT IDENTIFIER ::= { acosSlb 87 }
acosSlbServerGroupS                 OBJECT IDENTIFIER ::= { acosSlbServerGroup 1 }

slbServerGroupSTable OBJECT-TYPE
		SYNTAX SEQUENCE OF SlbServerGroupSEntry
		MAX-ACCESS not-accessible
		STATUS current
		::={ acosSlbServerGroupS 1 } 


	slbServerGroupSEntry OBJECT-TYPE
		SYNTAX SlbServerGroupSEntry
		MAX-ACCESS not-accessible
		STATUS current
		INDEX {
			name
		}
		::={ slbServerGroupSTable 1 } 


	SlbServerGroupSEntry ::=
		SEQUENCE {
			name DisplayString, 
			slbServerCurrRate CounterBasedGauge64
		}

			name OBJECT-TYPE
			SYNTAX  DisplayString 
			MAX-ACCESS read-only 
			STATUS current
			DESCRIPTION  "server-group name" 
			::={ slbServerGroupSEntry 1 } 

			slbServerCurrRate OBJECT-TYPE
			SYNTAX  CounterBasedGauge64 
			MAX-ACCESS read-only 
			STATUS current
			DESCRIPTION  "Current established connections" 
			::={ slbServerGroupSEntry 2 } 

acosSlbVirtualServer                OBJECT IDENTIFIER ::= { acosSlb 23 }
acosSlbVirtualServerPort            OBJECT IDENTIFIER ::= { acosSlbVirtualServer 2 }
acosSlbVirtualServerPortS           OBJECT IDENTIFIER ::= { acosSlbVirtualServerPort 1 }

slbVirtualServerPortSTable OBJECT-TYPE
		SYNTAX SEQUENCE OF SlbVirtualServerPortSEntry
		MAX-ACCESS not-accessible
		STATUS current
		::={ acosSlbVirtualServerPortS 1 } 


	slbVirtualServerPortSEntry OBJECT-TYPE
		SYNTAX SlbVirtualServerPortSEntry
		MAX-ACCESS not-accessible
		STATUS current
		INDEX {
			name,
			portNumber,
			protocol
		}
		::={ slbVirtualServerPortSTable 1 } 


	SlbVirtualServerPortSEntry ::=
		SEQUENCE {
			name DisplayString, 
			portNumber INTEGER, 
			protocol DisplayString, 
			slbSrvPortCurrConn CounterBasedGauge64,
			totalL4Conn CounterBasedGauge64,
			totalL7Conn CounterBasedGauge64,
			totalTcpConn CounterBasedGauge64,
			slbSrvPortTotalConn CounterBasedGauge64,
			totalFwdBytes CounterBasedGauge64,
			totalFwdPkts CounterBasedGauge64,
			totalRevBytes CounterBasedGauge64,
			totalRevPkts CounterBasedGauge64,
			totalDnsPkts CounterBasedGauge64,
			totalMfDnsPkts CounterBasedGauge64,
			esTotalFailureActions CounterBasedGauge64,
			compressionBytesBefore CounterBasedGauge64,
			compressionBytesAfter CounterBasedGauge64,
			compressionHit CounterBasedGauge64,
			compressionMiss CounterBasedGauge64,
			compressionMissNoClient CounterBasedGauge64,
			compressionMissTemplateExclusion CounterBasedGauge64,
			currReq CounterBasedGauge64,
			slbSrvPortTotalReq CounterBasedGauge64,
			totalReqSucc CounterBasedGauge64,
			slbSrvPortPeakConn CounterBasedGauge64,
			currConnRate CounterBasedGauge64,
			lastRspTime CounterBasedGauge64,
			fastestRspTime CounterBasedGauge64,
			slowestRspTime CounterBasedGauge64,
			locPermit CounterBasedGauge64,
			locDeny CounterBasedGauge64,
			locConn CounterBasedGauge64,
			currSslConn CounterBasedGauge64,
			totalSslConn CounterBasedGauge64,
			backendTimeToFirstByte CounterBasedGauge64,
			backendTimeToLastByte CounterBasedGauge64,
			inLatency CounterBasedGauge64,
			outLatency CounterBasedGauge64,
			totalFwdBytesOut CounterBasedGauge64,
			totalFwdPktsOut CounterBasedGauge64,
			totalRevBytesOut CounterBasedGauge64,
			totalRevPktsOut CounterBasedGauge64,
			currReqRate CounterBasedGauge64,
			currResp CounterBasedGauge64,
			totalResp CounterBasedGauge64,
			totalRespSucc CounterBasedGauge64,
			currRespRate CounterBasedGauge64,
			dnsrrlTotalAllowed CounterBasedGauge64,
			dnsrrlTotalDropped CounterBasedGauge64,
			dnsrrlTotalSlipped CounterBasedGauge64,
			dnsrrlBadFqdn CounterBasedGauge64,
			throughputBitsPerSec CounterBasedGauge64,
			dynamicMemoryAlloc CounterBasedGauge64,
			dynamicMemoryFree CounterBasedGauge64,
			dynamicMemory CounterBasedGauge64,
			ipOnlyLbFwdBytes CounterBasedGauge64,
			ipOnlyLbRevBytes CounterBasedGauge64,
			ipOnlyLbFwdPkts CounterBasedGauge64,
			ipOnlyLbRevPkts CounterBasedGauge64,
			totalDnsFilterTypeDrop CounterBasedGauge64,
			totalDnsFilterClassDrop CounterBasedGauge64,
			dnsFilterTypeADrop CounterBasedGauge64,
			dnsFilterTypeAaaaDrop CounterBasedGauge64,
			dnsFilterTypeCnameDrop CounterBasedGauge64,
			dnsFilterTypeMxDrop CounterBasedGauge64,
			dnsFilterTypeNsDrop CounterBasedGauge64,
			dnsFilterTypeSrvDrop CounterBasedGauge64,
			dnsFilterTypePtrDrop CounterBasedGauge64,
			dnsFilterTypeSoaDrop CounterBasedGauge64,
			dnsFilterTypeTxtDrop CounterBasedGauge64,
			dnsFilterTypeAnyDrop CounterBasedGauge64,
			dnsFilterTypeOthersDrop CounterBasedGauge64,
			dnsFilterClassInternetDrop CounterBasedGauge64,
			dnsFilterClassChaosDrop CounterBasedGauge64,
			dnsFilterClassHesiodDrop CounterBasedGauge64,
			dnsFilterClassNoneDrop CounterBasedGauge64,
			dnsFilterClassAnyDrop CounterBasedGauge64,
			dnsFilterClassOthersDrop CounterBasedGauge64,
			dnsRpzActionDrop CounterBasedGauge64,
			dnsRpzActionPassThru CounterBasedGauge64,
			dnsRpzActionTcpOnly CounterBasedGauge64,
			dnsRpzActionNxdomain CounterBasedGauge64,
			dnsRpzActionNodata CounterBasedGauge64,
			dnsRpzActionLocalData CounterBasedGauge64,
			dnsRpzTriggerClientIp CounterBasedGauge64,
			dnsRpzTriggerRespIp CounterBasedGauge64,
			dnsRpzTriggerNsIp CounterBasedGauge64,
			dnsRpzTriggerQname CounterBasedGauge64,
			dnsRpzTriggerNsName CounterBasedGauge64,
			compressionBytesBeforeBr CounterBasedGauge64,
			compressionBytesAfterBr CounterBasedGauge64,
			compressionBytesBeforeTotal CounterBasedGauge64,
			compressionBytesAfterTotal CounterBasedGauge64,
			compressionHitBr CounterBasedGauge64,
			compressionMissBr CounterBasedGauge64,
			compressionHitTotal CounterBasedGauge64,
			compressionMissTotal CounterBasedGauge64,
			dnsrrlTotalTc CounterBasedGauge64,
			http1ClientIdleTimeout CounterBasedGauge64,
			http2ClientIdleTimeout CounterBasedGauge64
		}

			name OBJECT-TYPE
			SYNTAX  DisplayString 
			MAX-ACCESS read-only 
			STATUS current
			DESCRIPTION  "SLB Virtual Server Name" 
			::={ slbVirtualServerPortSEntry 1 } 

			portNumber OBJECT-TYPE
			SYNTAX  INTEGER 
			MAX-ACCESS read-only 
			STATUS current
			DESCRIPTION  "Port" 
			::={ slbVirtualServerPortSEntry 2 } 

			protocol OBJECT-TYPE
			SYNTAX  DisplayString 
			MAX-ACCESS read-only 
			STATUS current
			DESCRIPTION  "protocol" 
			::={ slbVirtualServerPortSEntry 3 } 

			slbSrvPortCurrConn OBJECT-TYPE
			SYNTAX  CounterBasedGauge64 
			MAX-ACCESS read-only 
			STATUS current
			DESCRIPTION  "Current established connections" 
			::={ slbVirtualServerPortSEntry 4 } 

			totalL4Conn OBJECT-TYPE
			SYNTAX  CounterBasedGauge64 
			MAX-ACCESS read-only 
			STATUS current
			DESCRIPTION  "Total L4 connections established" 
			::={ slbVirtualServerPortSEntry 5 } 

			totalL7Conn OBJECT-TYPE
			SYNTAX  CounterBasedGauge64 
			MAX-ACCESS read-only 
			STATUS current
			DESCRIPTION  "Total L7 connections established" 
			::={ slbVirtualServerPortSEntry 6 } 

			totalTcpConn OBJECT-TYPE
			SYNTAX  CounterBasedGauge64 
			MAX-ACCESS read-only 
			STATUS current
			DESCRIPTION  "Total TCP connections established" 
			::={ slbVirtualServerPortSEntry 7 } 

			slbSrvPortTotalConn OBJECT-TYPE
			SYNTAX  CounterBasedGauge64 
			MAX-ACCESS read-only 
			STATUS current
			DESCRIPTION  "Total connections established" 
			::={ slbVirtualServerPortSEntry 8 } 

			totalFwdBytes OBJECT-TYPE
			SYNTAX  CounterBasedGauge64 
			MAX-ACCESS read-only 
			STATUS current
			DESCRIPTION  "Bytes processed in forward direction" 
			::={ slbVirtualServerPortSEntry 9 } 

			totalFwdPkts OBJECT-TYPE
			SYNTAX  CounterBasedGauge64 
			MAX-ACCESS read-only 
			STATUS current
			DESCRIPTION  "Packets processed in forward direction" 
			::={ slbVirtualServerPortSEntry 10 } 

			totalRevBytes OBJECT-TYPE
			SYNTAX  CounterBasedGauge64 
			MAX-ACCESS read-only 
			STATUS current
			DESCRIPTION  "Bytes processed in reverse direction" 
			::={ slbVirtualServerPortSEntry 11 } 

			totalRevPkts OBJECT-TYPE
			SYNTAX  CounterBasedGauge64 
			MAX-ACCESS read-only 
			STATUS current
			DESCRIPTION  "Packets processed in reverse direction" 
			::={ slbVirtualServerPortSEntry 12 } 

			totalDnsPkts OBJECT-TYPE
			SYNTAX  CounterBasedGauge64 
			MAX-ACCESS read-only 
			STATUS current
			DESCRIPTION  "Total DNS packets processed" 
			::={ slbVirtualServerPortSEntry 13 } 

			totalMfDnsPkts OBJECT-TYPE
			SYNTAX  CounterBasedGauge64 
			MAX-ACCESS read-only 
			STATUS current
			DESCRIPTION  "Total MF DNS packets" 
			::={ slbVirtualServerPortSEntry 14 } 

			esTotalFailureActions OBJECT-TYPE
			SYNTAX  CounterBasedGauge64 
			MAX-ACCESS read-only 
			STATUS current
			DESCRIPTION  "Total failure actions" 
			::={ slbVirtualServerPortSEntry 15 } 

			compressionBytesBefore OBJECT-TYPE
			SYNTAX  CounterBasedGauge64 
			MAX-ACCESS read-only 
			STATUS current
			DESCRIPTION  "Data into gzip compression engine" 
			::={ slbVirtualServerPortSEntry 16 } 

			compressionBytesAfter OBJECT-TYPE
			SYNTAX  CounterBasedGauge64 
			MAX-ACCESS read-only 
			STATUS current
			DESCRIPTION  "Data out of gzip compression engine" 
			::={ slbVirtualServerPortSEntry 17 } 

			compressionHit OBJECT-TYPE
			SYNTAX  CounterBasedGauge64 
			MAX-ACCESS read-only 
			STATUS current
			DESCRIPTION  "Number of requests compressed" 
			::={ slbVirtualServerPortSEntry 18 } 

			compressionMiss OBJECT-TYPE
			SYNTAX  CounterBasedGauge64 
			MAX-ACCESS read-only 
			STATUS current
			DESCRIPTION  "Number of requests NOT compressed" 
			::={ slbVirtualServerPortSEntry 19 } 

			compressionMissNoClient OBJECT-TYPE
			SYNTAX  CounterBasedGauge64 
			MAX-ACCESS read-only 
			STATUS current
			DESCRIPTION  "Compression miss no client" 
			::={ slbVirtualServerPortSEntry 20 } 

			compressionMissTemplateExclusion OBJECT-TYPE
			SYNTAX  CounterBasedGauge64 
			MAX-ACCESS read-only 
			STATUS current
			DESCRIPTION  "Compression miss template exclusion" 
			::={ slbVirtualServerPortSEntry 21 } 

			currReq OBJECT-TYPE
			SYNTAX  CounterBasedGauge64 
			MAX-ACCESS read-only 
			STATUS current
			DESCRIPTION  "Current requests" 
			::={ slbVirtualServerPortSEntry 22 } 

			slbSrvPortTotalReq OBJECT-TYPE
			SYNTAX  CounterBasedGauge64 
			MAX-ACCESS read-only 
			STATUS current
			DESCRIPTION  "Total requests" 
			::={ slbVirtualServerPortSEntry 23 } 

			totalReqSucc OBJECT-TYPE
			SYNTAX  CounterBasedGauge64 
			MAX-ACCESS read-only 
			STATUS current
			DESCRIPTION  "Total successful requests" 
			::={ slbVirtualServerPortSEntry 24 } 

			slbSrvPortPeakConn OBJECT-TYPE
			SYNTAX  CounterBasedGauge64 
			MAX-ACCESS read-only 
			STATUS current
			DESCRIPTION  "Peak connections" 
			::={ slbVirtualServerPortSEntry 25 } 

			currConnRate OBJECT-TYPE
			SYNTAX  CounterBasedGauge64 
			MAX-ACCESS read-only 
			STATUS current
			DESCRIPTION  "Current connection rate" 
			::={ slbVirtualServerPortSEntry 26 } 

			lastRspTime OBJECT-TYPE
			SYNTAX  CounterBasedGauge64 
			MAX-ACCESS read-only 
			STATUS current
			DESCRIPTION  "Last response time" 
			::={ slbVirtualServerPortSEntry 27 } 

			fastestRspTime OBJECT-TYPE
			SYNTAX  CounterBasedGauge64 
			MAX-ACCESS read-only 
			STATUS current
			DESCRIPTION  "Fastest response time" 
			::={ slbVirtualServerPortSEntry 28 } 

			slowestRspTime OBJECT-TYPE
			SYNTAX  CounterBasedGauge64 
			MAX-ACCESS read-only 
			STATUS current
			DESCRIPTION  "Slowest response time" 
			::={ slbVirtualServerPortSEntry 29 } 

			locPermit OBJECT-TYPE
			SYNTAX  CounterBasedGauge64 
			MAX-ACCESS read-only 
			STATUS current
			DESCRIPTION  "Geo-location Permit count" 
			::={ slbVirtualServerPortSEntry 30 } 

			locDeny OBJECT-TYPE
			SYNTAX  CounterBasedGauge64 
			MAX-ACCESS read-only 
			STATUS current
			DESCRIPTION  "Geo-location Deny count" 
			::={ slbVirtualServerPortSEntry 31 } 

			locConn OBJECT-TYPE
			SYNTAX  CounterBasedGauge64 
			MAX-ACCESS read-only 
			STATUS current
			DESCRIPTION  "Geo-location Connection count" 
			::={ slbVirtualServerPortSEntry 32 } 

			currSslConn OBJECT-TYPE
			SYNTAX  CounterBasedGauge64 
			MAX-ACCESS read-only 
			STATUS current
			DESCRIPTION  "Current SSL connections" 
			::={ slbVirtualServerPortSEntry 33 } 

			totalSslConn OBJECT-TYPE
			SYNTAX  CounterBasedGauge64 
			MAX-ACCESS read-only 
			STATUS current
			DESCRIPTION  "Total SSL connections" 
			::={ slbVirtualServerPortSEntry 34 } 

			backendTimeToFirstByte OBJECT-TYPE
			SYNTAX  CounterBasedGauge64 
			MAX-ACCESS read-only 
			STATUS current
			DESCRIPTION  "Backend Time from Request to Response First Byte" 
			::={ slbVirtualServerPortSEntry 35 } 

			backendTimeToLastByte OBJECT-TYPE
			SYNTAX  CounterBasedGauge64 
			MAX-ACCESS read-only 
			STATUS current
			DESCRIPTION  "Backend Time from Request to Response Last Byte" 
			::={ slbVirtualServerPortSEntry 36 } 

			inLatency OBJECT-TYPE
			SYNTAX  CounterBasedGauge64 
			MAX-ACCESS read-only 
			STATUS current
			DESCRIPTION  "Request Latency at Thunder" 
			::={ slbVirtualServerPortSEntry 37 } 

			outLatency OBJECT-TYPE
			SYNTAX  CounterBasedGauge64 
			MAX-ACCESS read-only 
			STATUS current
			DESCRIPTION  "Response Latency at Thunder" 
			::={ slbVirtualServerPortSEntry 38 } 

			totalFwdBytesOut OBJECT-TYPE
			SYNTAX  CounterBasedGauge64 
			MAX-ACCESS read-only 
			STATUS current
			DESCRIPTION  "Bytes processed in forward direction (outbound)" 
			::={ slbVirtualServerPortSEntry 39 } 

			totalFwdPktsOut OBJECT-TYPE
			SYNTAX  CounterBasedGauge64 
			MAX-ACCESS read-only 
			STATUS current
			DESCRIPTION  "Packets processed in forward direction (outbound)" 
			::={ slbVirtualServerPortSEntry 40 } 

			totalRevBytesOut OBJECT-TYPE
			SYNTAX  CounterBasedGauge64 
			MAX-ACCESS read-only 
			STATUS current
			DESCRIPTION  "Bytes processed in reverse direction (outbound)" 
			::={ slbVirtualServerPortSEntry 41 } 

			totalRevPktsOut OBJECT-TYPE
			SYNTAX  CounterBasedGauge64 
			MAX-ACCESS read-only 
			STATUS current
			DESCRIPTION  "Packets processed in reverse direction (outbound)" 
			::={ slbVirtualServerPortSEntry 42 } 

			currReqRate OBJECT-TYPE
			SYNTAX  CounterBasedGauge64 
			MAX-ACCESS read-only 
			STATUS current
			DESCRIPTION  "Current request rate" 
			::={ slbVirtualServerPortSEntry 43 } 

			currResp OBJECT-TYPE
			SYNTAX  CounterBasedGauge64 
			MAX-ACCESS read-only 
			STATUS current
			DESCRIPTION  "Current response" 
			::={ slbVirtualServerPortSEntry 44 } 

			totalResp OBJECT-TYPE
			SYNTAX  CounterBasedGauge64 
			MAX-ACCESS read-only 
			STATUS current
			DESCRIPTION  "Total response" 
			::={ slbVirtualServerPortSEntry 45 } 

			totalRespSucc OBJECT-TYPE
			SYNTAX  CounterBasedGauge64 
			MAX-ACCESS read-only 
			STATUS current
			DESCRIPTION  "Total successful responses" 
			::={ slbVirtualServerPortSEntry 46 } 

			currRespRate OBJECT-TYPE
			SYNTAX  CounterBasedGauge64 
			MAX-ACCESS read-only 
			STATUS current
			DESCRIPTION  "Current response rate" 
			::={ slbVirtualServerPortSEntry 47 } 

			dnsrrlTotalAllowed OBJECT-TYPE
			SYNTAX  CounterBasedGauge64 
			MAX-ACCESS read-only 
			STATUS current
			DESCRIPTION  "DNS Response-Rate-Limiting Total Responses Allowed" 
			::={ slbVirtualServerPortSEntry 48 } 

			dnsrrlTotalDropped OBJECT-TYPE
			SYNTAX  CounterBasedGauge64 
			MAX-ACCESS read-only 
			STATUS current
			DESCRIPTION  "DNS Response-Rate-Limiting Total Responses Dropped" 
			::={ slbVirtualServerPortSEntry 49 } 

			dnsrrlTotalSlipped OBJECT-TYPE
			SYNTAX  CounterBasedGauge64 
			MAX-ACCESS read-only 
			STATUS current
			DESCRIPTION  "DNS Response-Rate-Limiting Total Responses Slipped" 
			::={ slbVirtualServerPortSEntry 50 } 

			dnsrrlBadFqdn OBJECT-TYPE
			SYNTAX  CounterBasedGauge64 
			MAX-ACCESS read-only 
			STATUS current
			DESCRIPTION  "DNS Response-Rate-Limiting Bad FQDN" 
			::={ slbVirtualServerPortSEntry 51 } 

			throughputBitsPerSec OBJECT-TYPE
			SYNTAX  CounterBasedGauge64 
			MAX-ACCESS read-only 
			STATUS current
			DESCRIPTION  "Throughput in bits/sec" 
			::={ slbVirtualServerPortSEntry 52 } 

			dynamicMemoryAlloc OBJECT-TYPE
			SYNTAX  CounterBasedGauge64 
			MAX-ACCESS read-only 
			STATUS current
			DESCRIPTION  "dynamic memory (bytes) allocated by the vport" 
			::={ slbVirtualServerPortSEntry 53 } 

			dynamicMemoryFree OBJECT-TYPE
			SYNTAX  CounterBasedGauge64 
			MAX-ACCESS read-only 
			STATUS current
			DESCRIPTION  "dynamic memory (bytes) allocated by the vport" 
			::={ slbVirtualServerPortSEntry 54 } 

			dynamicMemory OBJECT-TYPE
			SYNTAX  CounterBasedGauge64 
			MAX-ACCESS read-only 
			STATUS current
			DESCRIPTION  "dynamic memory (bytes) used by the vport(alloc-free)" 
			::={ slbVirtualServerPortSEntry 55 } 

			ipOnlyLbFwdBytes OBJECT-TYPE
			SYNTAX  CounterBasedGauge64 
			MAX-ACCESS read-only 
			STATUS current
			DESCRIPTION  "IP-Only-LB Bytes processed in forward direction" 
			::={ slbVirtualServerPortSEntry 56 } 

			ipOnlyLbRevBytes OBJECT-TYPE
			SYNTAX  CounterBasedGauge64 
			MAX-ACCESS read-only 
			STATUS current
			DESCRIPTION  "IP-Only-LB Bytes processed in reverse direction" 
			::={ slbVirtualServerPortSEntry 57 } 

			ipOnlyLbFwdPkts OBJECT-TYPE
			SYNTAX  CounterBasedGauge64 
			MAX-ACCESS read-only 
			STATUS current
			DESCRIPTION  "IP-Only-LB Packets processed in forward direction" 
			::={ slbVirtualServerPortSEntry 58 } 

			ipOnlyLbRevPkts OBJECT-TYPE
			SYNTAX  CounterBasedGauge64 
			MAX-ACCESS read-only 
			STATUS current
			DESCRIPTION  "IP-Only-LB Packets processed in reverse direction" 
			::={ slbVirtualServerPortSEntry 59 } 

			totalDnsFilterTypeDrop OBJECT-TYPE
			SYNTAX  CounterBasedGauge64 
			MAX-ACCESS read-only 
			STATUS current
			DESCRIPTION  "Total DNS Filter Type Drop" 
			::={ slbVirtualServerPortSEntry 60 } 

			totalDnsFilterClassDrop OBJECT-TYPE
			SYNTAX  CounterBasedGauge64 
			MAX-ACCESS read-only 
			STATUS current
			DESCRIPTION  "Total DNS Filter Class Drop" 
			::={ slbVirtualServerPortSEntry 61 } 

			dnsFilterTypeADrop OBJECT-TYPE
			SYNTAX  CounterBasedGauge64 
			MAX-ACCESS read-only 
			STATUS current
			DESCRIPTION  "DNS Filter Type A Drop" 
			::={ slbVirtualServerPortSEntry 62 } 

			dnsFilterTypeAaaaDrop OBJECT-TYPE
			SYNTAX  CounterBasedGauge64 
			MAX-ACCESS read-only 
			STATUS current
			DESCRIPTION  "DNS Filter Type AAAA Drop" 
			::={ slbVirtualServerPortSEntry 63 } 

			dnsFilterTypeCnameDrop OBJECT-TYPE
			SYNTAX  CounterBasedGauge64 
			MAX-ACCESS read-only 
			STATUS current
			DESCRIPTION  "DNS Filter Type CNAME Drop" 
			::={ slbVirtualServerPortSEntry 64 } 

			dnsFilterTypeMxDrop OBJECT-TYPE
			SYNTAX  CounterBasedGauge64 
			MAX-ACCESS read-only 
			STATUS current
			DESCRIPTION  "DNS Filter Type MX Drop" 
			::={ slbVirtualServerPortSEntry 65 } 

			dnsFilterTypeNsDrop OBJECT-TYPE
			SYNTAX  CounterBasedGauge64 
			MAX-ACCESS read-only 
			STATUS current
			DESCRIPTION  "DNS Filter Type NS Drop" 
			::={ slbVirtualServerPortSEntry 66 } 

			dnsFilterTypeSrvDrop OBJECT-TYPE
			SYNTAX  CounterBasedGauge64 
			MAX-ACCESS read-only 
			STATUS current
			DESCRIPTION  "DNS Filter Type SRV Drop" 
			::={ slbVirtualServerPortSEntry 67 } 

			dnsFilterTypePtrDrop OBJECT-TYPE
			SYNTAX  CounterBasedGauge64 
			MAX-ACCESS read-only 
			STATUS current
			DESCRIPTION  "DNS Filter Type PTR Drop" 
			::={ slbVirtualServerPortSEntry 68 } 

			dnsFilterTypeSoaDrop OBJECT-TYPE
			SYNTAX  CounterBasedGauge64 
			MAX-ACCESS read-only 
			STATUS current
			DESCRIPTION  "DNS Filter Type SOA Drop" 
			::={ slbVirtualServerPortSEntry 69 } 

			dnsFilterTypeTxtDrop OBJECT-TYPE
			SYNTAX  CounterBasedGauge64 
			MAX-ACCESS read-only 
			STATUS current
			DESCRIPTION  "DNS Filter Type TXT Drop" 
			::={ slbVirtualServerPortSEntry 70 } 

			dnsFilterTypeAnyDrop OBJECT-TYPE
			SYNTAX  CounterBasedGauge64 
			MAX-ACCESS read-only 
			STATUS current
			DESCRIPTION  "DNS Filter Type Any Drop" 
			::={ slbVirtualServerPortSEntry 71 } 

			dnsFilterTypeOthersDrop OBJECT-TYPE
			SYNTAX  CounterBasedGauge64 
			MAX-ACCESS read-only 
			STATUS current
			DESCRIPTION  "DNS Filter Type OTHERS Drop" 
			::={ slbVirtualServerPortSEntry 72 } 

			dnsFilterClassInternetDrop OBJECT-TYPE
			SYNTAX  CounterBasedGauge64 
			MAX-ACCESS read-only 
			STATUS current
			DESCRIPTION  "DNS Filter Class INTERNET Drop" 
			::={ slbVirtualServerPortSEntry 73 } 

			dnsFilterClassChaosDrop OBJECT-TYPE
			SYNTAX  CounterBasedGauge64 
			MAX-ACCESS read-only 
			STATUS current
			DESCRIPTION  "DNS Filter Class CHAOS Drop" 
			::={ slbVirtualServerPortSEntry 74 } 

			dnsFilterClassHesiodDrop OBJECT-TYPE
			SYNTAX  CounterBasedGauge64 
			MAX-ACCESS read-only 
			STATUS current
			DESCRIPTION  "DNS Filter Class HESIOD Drop" 
			::={ slbVirtualServerPortSEntry 75 } 

			dnsFilterClassNoneDrop OBJECT-TYPE
			SYNTAX  CounterBasedGauge64 
			MAX-ACCESS read-only 
			STATUS current
			DESCRIPTION  "DNS Filter Class NONE Drop" 
			::={ slbVirtualServerPortSEntry 76 } 

			dnsFilterClassAnyDrop OBJECT-TYPE
			SYNTAX  CounterBasedGauge64 
			MAX-ACCESS read-only 
			STATUS current
			DESCRIPTION  "DNS Filter Class ANY Drop" 
			::={ slbVirtualServerPortSEntry 77 } 

			dnsFilterClassOthersDrop OBJECT-TYPE
			SYNTAX  CounterBasedGauge64 
			MAX-ACCESS read-only 
			STATUS current
			DESCRIPTION  "DNS Filter Class OTHERS Drop" 
			::={ slbVirtualServerPortSEntry 78 } 

			dnsRpzActionDrop OBJECT-TYPE
			SYNTAX  CounterBasedGauge64 
			MAX-ACCESS read-only 
			STATUS current
			DESCRIPTION  "DNS RPZ Action Drop" 
			::={ slbVirtualServerPortSEntry 79 } 

			dnsRpzActionPassThru OBJECT-TYPE
			SYNTAX  CounterBasedGauge64 
			MAX-ACCESS read-only 
			STATUS current
			DESCRIPTION  "DNS RPZ Action Pass Through" 
			::={ slbVirtualServerPortSEntry 80 } 

			dnsRpzActionTcpOnly OBJECT-TYPE
			SYNTAX  CounterBasedGauge64 
			MAX-ACCESS read-only 
			STATUS current
			DESCRIPTION  "DNS RPZ Action TCP Only" 
			::={ slbVirtualServerPortSEntry 81 } 

			dnsRpzActionNxdomain OBJECT-TYPE
			SYNTAX  CounterBasedGauge64 
			MAX-ACCESS read-only 
			STATUS current
			DESCRIPTION  "DNS RPZ Action NXDOMAIN" 
			::={ slbVirtualServerPortSEntry 82 } 

			dnsRpzActionNodata OBJECT-TYPE
			SYNTAX  CounterBasedGauge64 
			MAX-ACCESS read-only 
			STATUS current
			DESCRIPTION  "DNS RPZ Action NODATA" 
			::={ slbVirtualServerPortSEntry 83 } 

			dnsRpzActionLocalData OBJECT-TYPE
			SYNTAX  CounterBasedGauge64 
			MAX-ACCESS read-only 
			STATUS current
			DESCRIPTION  "DNS RPZ Action Local Data" 
			::={ slbVirtualServerPortSEntry 84 } 

			dnsRpzTriggerClientIp OBJECT-TYPE
			SYNTAX  CounterBasedGauge64 
			MAX-ACCESS read-only 
			STATUS current
			DESCRIPTION  "DNS RPZ Trigger Client IP" 
			::={ slbVirtualServerPortSEntry 85 } 

			dnsRpzTriggerRespIp OBJECT-TYPE
			SYNTAX  CounterBasedGauge64 
			MAX-ACCESS read-only 
			STATUS current
			DESCRIPTION  "DNS RPZ Trigger Response IP" 
			::={ slbVirtualServerPortSEntry 86 } 

			dnsRpzTriggerNsIp OBJECT-TYPE
			SYNTAX  CounterBasedGauge64 
			MAX-ACCESS read-only 
			STATUS current
			DESCRIPTION  "DNS RPZ Trigger NS IP" 
			::={ slbVirtualServerPortSEntry 87 } 

			dnsRpzTriggerQname OBJECT-TYPE
			SYNTAX  CounterBasedGauge64 
			MAX-ACCESS read-only 
			STATUS current
			DESCRIPTION  "DNS RPZ Trigger Qname IP" 
			::={ slbVirtualServerPortSEntry 88 } 

			dnsRpzTriggerNsName OBJECT-TYPE
			SYNTAX  CounterBasedGauge64 
			MAX-ACCESS read-only 
			STATUS current
			DESCRIPTION  "DNS RPZ Trigger NS Name" 
			::={ slbVirtualServerPortSEntry 89 } 

			compressionBytesBeforeBr OBJECT-TYPE
			SYNTAX  CounterBasedGauge64 
			MAX-ACCESS read-only 
			STATUS current
			DESCRIPTION  "Data into brotli compression engine" 
			::={ slbVirtualServerPortSEntry 90 } 

			compressionBytesAfterBr OBJECT-TYPE
			SYNTAX  CounterBasedGauge64 
			MAX-ACCESS read-only 
			STATUS current
			DESCRIPTION  "Data out of brotli compression engine" 
			::={ slbVirtualServerPortSEntry 91 } 

			compressionBytesBeforeTotal OBJECT-TYPE
			SYNTAX  CounterBasedGauge64 
			MAX-ACCESS read-only 
			STATUS current
			DESCRIPTION  "Data into compression engine" 
			::={ slbVirtualServerPortSEntry 92 } 

			compressionBytesAfterTotal OBJECT-TYPE
			SYNTAX  CounterBasedGauge64 
			MAX-ACCESS read-only 
			STATUS current
			DESCRIPTION  "Data out of compression engine" 
			::={ slbVirtualServerPortSEntry 93 } 

			compressionHitBr OBJECT-TYPE
			SYNTAX  CounterBasedGauge64 
			MAX-ACCESS read-only 
			STATUS current
			DESCRIPTION  "Number of requests compressed with brotli" 
			::={ slbVirtualServerPortSEntry 94 } 

			compressionMissBr OBJECT-TYPE
			SYNTAX  CounterBasedGauge64 
			MAX-ACCESS read-only 
			STATUS current
			DESCRIPTION  "Number of requests NOT compressed with brotli" 
			::={ slbVirtualServerPortSEntry 95 } 

			compressionHitTotal OBJECT-TYPE
			SYNTAX  CounterBasedGauge64 
			MAX-ACCESS read-only 
			STATUS current
			DESCRIPTION  "Number of requests compressed" 
			::={ slbVirtualServerPortSEntry 96 } 

			compressionMissTotal OBJECT-TYPE
			SYNTAX  CounterBasedGauge64 
			MAX-ACCESS read-only 
			STATUS current
			DESCRIPTION  "Number of requests NOT compressed" 
			::={ slbVirtualServerPortSEntry 97 } 

			dnsrrlTotalTc OBJECT-TYPE
			SYNTAX  CounterBasedGauge64 
			MAX-ACCESS read-only 
			STATUS current
			DESCRIPTION  "DNS Response-Rate-Limiting Total Responses Replied With Truncated" 
			::={ slbVirtualServerPortSEntry 98 } 

			http1ClientIdleTimeout OBJECT-TYPE
			SYNTAX  CounterBasedGauge64 
			MAX-ACCESS read-only 
			STATUS current
			DESCRIPTION  "HTTP1 Client Idle Timeout" 
			::={ slbVirtualServerPortSEntry 99 } 

			http2ClientIdleTimeout OBJECT-TYPE
			SYNTAX  CounterBasedGauge64 
			MAX-ACCESS read-only 
			STATUS current
			DESCRIPTION  "HTTP2 Client Idle Timeout" 
			::={ slbVirtualServerPortSEntry 100 } 

acosSlbFtpData                      OBJECT IDENTIFIER ::= { acosSlb 24 }
acosSlbFtpDataS                     OBJECT IDENTIFIER ::= { acosSlbFtpData 1 }

		slbFtpDataSessionNum OBJECT-TYPE
		SYNTAX  CounterBasedGauge64 
		MAX-ACCESS read-only 
		STATUS current
		DESCRIPTION  "Total Data Sessions" 
		::={ acosSlbFtpDataS 1 } 

		portOutOfRange OBJECT-TYPE
		SYNTAX  CounterBasedGauge64 
		MAX-ACCESS read-only 
		STATUS current
		DESCRIPTION  "Drop Data Port out of range" 
		::={ acosSlbFtpDataS 2 } 

acosSlbConnectionReuse              OBJECT IDENTIFIER ::= { acosSlb 25 }
acosSlbConnectionReuseS             OBJECT IDENTIFIER ::= { acosSlbConnectionReuse 1 }

		currentOpen OBJECT-TYPE
		SYNTAX  CounterBasedGauge64 
		MAX-ACCESS read-only 
		STATUS current
		DESCRIPTION  "Open persist" 
		::={ acosSlbConnectionReuseS 1 } 

		currentActive OBJECT-TYPE
		SYNTAX  CounterBasedGauge64 
		MAX-ACCESS read-only 
		STATUS current
		DESCRIPTION  "Active persist" 
		::={ acosSlbConnectionReuseS 2 } 

		nbind OBJECT-TYPE
		SYNTAX  CounterBasedGauge64 
		MAX-ACCESS read-only 
		STATUS current
		DESCRIPTION  "Total bind" 
		::={ acosSlbConnectionReuseS 3 } 

		nunbind OBJECT-TYPE
		SYNTAX  CounterBasedGauge64 
		MAX-ACCESS read-only 
		STATUS current
		DESCRIPTION  "Total unbind" 
		::={ acosSlbConnectionReuseS 4 } 

		nestab OBJECT-TYPE
		SYNTAX  CounterBasedGauge64 
		MAX-ACCESS read-only 
		STATUS current
		DESCRIPTION  "Total established" 
		::={ acosSlbConnectionReuseS 5 } 

		ntermi OBJECT-TYPE
		SYNTAX  CounterBasedGauge64 
		MAX-ACCESS read-only 
		STATUS current
		DESCRIPTION  "Total terminated" 
		::={ acosSlbConnectionReuseS 6 } 

		ntermiErr OBJECT-TYPE
		SYNTAX  CounterBasedGauge64 
		MAX-ACCESS read-only 
		STATUS current
		DESCRIPTION  "Total terminated by err" 
		::={ acosSlbConnectionReuseS 7 } 

		delayUnbind OBJECT-TYPE
		SYNTAX  CounterBasedGauge64 
		MAX-ACCESS read-only 
		STATUS current
		DESCRIPTION  "Delayed unbind" 
		::={ acosSlbConnectionReuseS 8 } 

		longResp OBJECT-TYPE
		SYNTAX  CounterBasedGauge64 
		MAX-ACCESS read-only 
		STATUS current
		DESCRIPTION  "Long resp" 
		::={ acosSlbConnectionReuseS 9 } 

		missResp OBJECT-TYPE
		SYNTAX  CounterBasedGauge64 
		MAX-ACCESS read-only 
		STATUS current
		DESCRIPTION  "Missed resp" 
		::={ acosSlbConnectionReuseS 10 } 

		unboundDataRcv OBJECT-TYPE
		SYNTAX  CounterBasedGauge64 
		MAX-ACCESS read-only 
		STATUS current
		DESCRIPTION  "Unbound data rcvd" 
		::={ acosSlbConnectionReuseS 11 } 

		slbConnectionReusePauseConn OBJECT-TYPE
		SYNTAX  CounterBasedGauge64 
		MAX-ACCESS read-only 
		STATUS current
		DESCRIPTION  "Pause request" 
		::={ acosSlbConnectionReuseS 12 } 

		slbConnectionReusePauseConnFail OBJECT-TYPE
		SYNTAX  CounterBasedGauge64 
		MAX-ACCESS read-only 
		STATUS current
		DESCRIPTION  "Pause request fail" 
		::={ acosSlbConnectionReuseS 13 } 

		slbConnectionReuseResumeConn OBJECT-TYPE
		SYNTAX  CounterBasedGauge64 
		MAX-ACCESS read-only 
		STATUS current
		DESCRIPTION  "Resume request" 
		::={ acosSlbConnectionReuseS 14 } 

		notRemoveFromRport OBJECT-TYPE
		SYNTAX  CounterBasedGauge64 
		MAX-ACCESS read-only 
		STATUS current
		DESCRIPTION  "Not remove from list" 
		::={ acosSlbConnectionReuseS 15 } 

		zeroPconnValue OBJECT-TYPE
		SYNTAX  CounterBasedGauge64 
		MAX-ACCESS read-only 
		STATUS current
		DESCRIPTION  "Zero current pconn counter value" 
		::={ acosSlbConnectionReuseS 16 } 

		zeroPconnBindValue OBJECT-TYPE
		SYNTAX  CounterBasedGauge64 
		MAX-ACCESS read-only 
		STATUS current
		DESCRIPTION  "Zero current pconn bind counter value" 
		::={ acosSlbConnectionReuseS 17 } 

		currentHttp1ConnInThePool OBJECT-TYPE
		SYNTAX  CounterBasedGauge64 
		MAX-ACCESS read-only 
		STATUS current
		DESCRIPTION  "Current http1 conn in the pool" 
		::={ acosSlbConnectionReuseS 18 } 

		currentHttp2ConnInThePool OBJECT-TYPE
		SYNTAX  CounterBasedGauge64 
		MAX-ACCESS read-only 
		STATUS current
		DESCRIPTION  "Current http2 conn in the pool" 
		::={ acosSlbConnectionReuseS 19 } 

acosSlbAflow                        OBJECT IDENTIFIER ::= { acosSlb 26 }
acosSlbAflowS                       OBJECT IDENTIFIER ::= { acosSlbAflow 1 }

		pauseConn OBJECT-TYPE
		SYNTAX  CounterBasedGauge64 
		MAX-ACCESS read-only 
		STATUS current
		DESCRIPTION  "Pause connection" 
		::={ acosSlbAflowS 1 } 

		pauseConnFail OBJECT-TYPE
		SYNTAX  CounterBasedGauge64 
		MAX-ACCESS read-only 
		STATUS current
		DESCRIPTION  "Pause connection fail" 
		::={ acosSlbAflowS 2 } 

		resumeConn OBJECT-TYPE
		SYNTAX  CounterBasedGauge64 
		MAX-ACCESS read-only 
		STATUS current
		DESCRIPTION  "Resume connection" 
		::={ acosSlbAflowS 3 } 

		eventResumeConn OBJECT-TYPE
		SYNTAX  CounterBasedGauge64 
		MAX-ACCESS read-only 
		STATUS current
		DESCRIPTION  "Resume conn by event" 
		::={ acosSlbAflowS 4 } 

		timerResumeConn OBJECT-TYPE
		SYNTAX  CounterBasedGauge64 
		MAX-ACCESS read-only 
		STATUS current
		DESCRIPTION  "Resume conn by timer" 
		::={ acosSlbAflowS 5 } 

		tryToResumeConn OBJECT-TYPE
		SYNTAX  CounterBasedGauge64 
		MAX-ACCESS read-only 
		STATUS current
		DESCRIPTION  "Resume conn by trying" 
		::={ acosSlbAflowS 6 } 

		retryResumeConn OBJECT-TYPE
		SYNTAX  CounterBasedGauge64 
		MAX-ACCESS read-only 
		STATUS current
		DESCRIPTION  "Resume conn by retry" 
		::={ acosSlbAflowS 7 } 

		errorResumeConn OBJECT-TYPE
		SYNTAX  CounterBasedGauge64 
		MAX-ACCESS read-only 
		STATUS current
		DESCRIPTION  "Resume conn by error" 
		::={ acosSlbAflowS 8 } 

		openNewServerConn OBJECT-TYPE
		SYNTAX  CounterBasedGauge64 
		MAX-ACCESS read-only 
		STATUS current
		DESCRIPTION  "Open new server conn" 
		::={ acosSlbAflowS 9 } 

		reuseServerIdleConn OBJECT-TYPE
		SYNTAX  CounterBasedGauge64 
		MAX-ACCESS read-only 
		STATUS current
		DESCRIPTION  "Reuse idle server conn" 
		::={ acosSlbAflowS 10 } 

		incAflowLimit OBJECT-TYPE
		SYNTAX  CounterBasedGauge64 
		MAX-ACCESS read-only 
		STATUS current
		DESCRIPTION  "Inc aFlow limit" 
		::={ acosSlbAflowS 11 } 

acosSlbFix                          OBJECT IDENTIFIER ::= { acosSlb 27 }
acosSlbFixS                         OBJECT IDENTIFIER ::= { acosSlbFix 1 }

		slbFixCurrProxy OBJECT-TYPE
		SYNTAX  CounterBasedGauge64 
		MAX-ACCESS read-only 
		STATUS current
		DESCRIPTION  "Current proxy conns" 
		::={ acosSlbFixS 1 } 

		slbFixTotalProxy OBJECT-TYPE
		SYNTAX  CounterBasedGauge64 
		MAX-ACCESS read-only 
		STATUS current
		DESCRIPTION  "Total proxy conns" 
		::={ acosSlbFixS 2 } 

		slbFixSvrselFail OBJECT-TYPE
		SYNTAX  CounterBasedGauge64 
		MAX-ACCESS read-only 
		STATUS current
		DESCRIPTION  "Server selection failure" 
		::={ acosSlbFixS 3 } 

		slbFixNoroute OBJECT-TYPE
		SYNTAX  CounterBasedGauge64 
		MAX-ACCESS read-only 
		STATUS current
		DESCRIPTION  "No route failure" 
		::={ acosSlbFixS 4 } 

		slbFixSnatFail OBJECT-TYPE
		SYNTAX  CounterBasedGauge64 
		MAX-ACCESS read-only 
		STATUS current
		DESCRIPTION  "Source NAT failure" 
		::={ acosSlbFixS 5 } 

		clientErr OBJECT-TYPE
		SYNTAX  CounterBasedGauge64 
		MAX-ACCESS read-only 
		STATUS current
		DESCRIPTION  "Client fail" 
		::={ acosSlbFixS 6 } 

		serverErr OBJECT-TYPE
		SYNTAX  CounterBasedGauge64 
		MAX-ACCESS read-only 
		STATUS current
		DESCRIPTION  "Server fail" 
		::={ acosSlbFixS 7 } 

		insertClientip OBJECT-TYPE
		SYNTAX  CounterBasedGauge64 
		MAX-ACCESS read-only 
		STATUS current
		DESCRIPTION  "Insert client IP" 
		::={ acosSlbFixS 9 } 

		defaultSwitching OBJECT-TYPE
		SYNTAX  CounterBasedGauge64 
		MAX-ACCESS read-only 
		STATUS current
		DESCRIPTION  "Default switching" 
		::={ acosSlbFixS 10 } 

		senderSwitching OBJECT-TYPE
		SYNTAX  CounterBasedGauge64 
		MAX-ACCESS read-only 
		STATUS current
		DESCRIPTION  "Sender ID switching" 
		::={ acosSlbFixS 11 } 

		targetSwitching OBJECT-TYPE
		SYNTAX  CounterBasedGauge64 
		MAX-ACCESS read-only 
		STATUS current
		DESCRIPTION  "Target ID switching" 
		::={ acosSlbFixS 12 } 

		clientTlsConn OBJECT-TYPE
		SYNTAX  CounterBasedGauge64 
		MAX-ACCESS read-only 
		STATUS current
		DESCRIPTION  "Client TLS conn" 
		::={ acosSlbFixS 13 } 

		serverTlsConn OBJECT-TYPE
		SYNTAX  CounterBasedGauge64 
		MAX-ACCESS read-only 
		STATUS current
		DESCRIPTION  "Server TLS conn" 
		::={ acosSlbFixS 14 } 

acosSlbSpdyProxy                    OBJECT IDENTIFIER ::= { acosSlb 28 }
acosSlbSpdyProxyS                   OBJECT IDENTIFIER ::= { acosSlbSpdyProxy 1 }

		slbSpdyProxyCurrProxy OBJECT-TYPE
		SYNTAX  CounterBasedGauge64 
		MAX-ACCESS read-only 
		STATUS current
		DESCRIPTION  "Curr Proxy Conns" 
		::={ acosSlbSpdyProxyS 1 } 

		slbSpdyProxyTotalProxy OBJECT-TYPE
		SYNTAX  CounterBasedGauge64 
		MAX-ACCESS read-only 
		STATUS current
		DESCRIPTION  "Total Proxy Conns" 
		::={ acosSlbSpdyProxyS 2 } 

		currHttpProxy OBJECT-TYPE
		SYNTAX  CounterBasedGauge64 
		MAX-ACCESS read-only 
		STATUS current
		DESCRIPTION  "Curr HTTP Proxy Conns" 
		::={ acosSlbSpdyProxyS 3 } 

		totalHttpProxy OBJECT-TYPE
		SYNTAX  CounterBasedGauge64 
		MAX-ACCESS read-only 
		STATUS current
		DESCRIPTION  "Total HTTP Proxy Conns" 
		::={ acosSlbSpdyProxyS 4 } 

		totalV2Proxy OBJECT-TYPE
		SYNTAX  CounterBasedGauge64 
		MAX-ACCESS read-only 
		STATUS current
		DESCRIPTION  "Version 2 Streams" 
		::={ acosSlbSpdyProxyS 5 } 

		totalV3Proxy OBJECT-TYPE
		SYNTAX  CounterBasedGauge64 
		MAX-ACCESS read-only 
		STATUS current
		DESCRIPTION  "Version 3 Streams" 
		::={ acosSlbSpdyProxyS 6 } 

		currStream OBJECT-TYPE
		SYNTAX  CounterBasedGauge64 
		MAX-ACCESS read-only 
		STATUS current
		DESCRIPTION  "Curr Streams" 
		::={ acosSlbSpdyProxyS 7 } 

		totalStream OBJECT-TYPE
		SYNTAX  CounterBasedGauge64 
		MAX-ACCESS read-only 
		STATUS current
		DESCRIPTION  "Total Streams" 
		::={ acosSlbSpdyProxyS 8 } 

		totalStreamSucc OBJECT-TYPE
		SYNTAX  CounterBasedGauge64 
		MAX-ACCESS read-only 
		STATUS current
		DESCRIPTION  "Streams(succ)" 
		::={ acosSlbSpdyProxyS 9 } 

		clientRst OBJECT-TYPE
		SYNTAX  CounterBasedGauge64 
		MAX-ACCESS read-only 
		STATUS current
		DESCRIPTION  "" 
		::={ acosSlbSpdyProxyS 10 } 

		serverRst OBJECT-TYPE
		SYNTAX  CounterBasedGauge64 
		MAX-ACCESS read-only 
		STATUS current
		DESCRIPTION  "Server RST sent" 
		::={ acosSlbSpdyProxyS 11 } 

		clientGoaway OBJECT-TYPE
		SYNTAX  CounterBasedGauge64 
		MAX-ACCESS read-only 
		STATUS current
		DESCRIPTION  "" 
		::={ acosSlbSpdyProxyS 12 } 

		serverGoaway OBJECT-TYPE
		SYNTAX  CounterBasedGauge64 
		MAX-ACCESS read-only 
		STATUS current
		DESCRIPTION  "Server GOAWAY sent" 
		::={ acosSlbSpdyProxyS 13 } 

		tcpErr OBJECT-TYPE
		SYNTAX  CounterBasedGauge64 
		MAX-ACCESS read-only 
		STATUS current
		DESCRIPTION  "TCP sock error" 
		::={ acosSlbSpdyProxyS 14 } 

		inflateCtx OBJECT-TYPE
		SYNTAX  CounterBasedGauge64 
		MAX-ACCESS read-only 
		STATUS current
		DESCRIPTION  "Inflate context" 
		::={ acosSlbSpdyProxyS 15 } 

		deflateCtx OBJECT-TYPE
		SYNTAX  CounterBasedGauge64 
		MAX-ACCESS read-only 
		STATUS current
		DESCRIPTION  "Deflate context" 
		::={ acosSlbSpdyProxyS 16 } 

		pingSent OBJECT-TYPE
		SYNTAX  CounterBasedGauge64 
		MAX-ACCESS read-only 
		STATUS current
		DESCRIPTION  "PING sent" 
		::={ acosSlbSpdyProxyS 17 } 

		streamNotFound OBJECT-TYPE
		SYNTAX  CounterBasedGauge64 
		MAX-ACCESS read-only 
		STATUS current
		DESCRIPTION  "STREAM not found" 
		::={ acosSlbSpdyProxyS 18 } 

		slbSpdyProxyClientFin OBJECT-TYPE
		SYNTAX  CounterBasedGauge64 
		MAX-ACCESS read-only 
		STATUS current
		DESCRIPTION  "Client FIN" 
		::={ acosSlbSpdyProxyS 19 } 

		slbSpdyProxyServerFin OBJECT-TYPE
		SYNTAX  CounterBasedGauge64 
		MAX-ACCESS read-only 
		STATUS current
		DESCRIPTION  "Server FIN" 
		::={ acosSlbSpdyProxyS 20 } 

		streamClose OBJECT-TYPE
		SYNTAX  CounterBasedGauge64 
		MAX-ACCESS read-only 
		STATUS current
		DESCRIPTION  "Stream close" 
		::={ acosSlbSpdyProxyS 21 } 

		streamErr OBJECT-TYPE
		SYNTAX  CounterBasedGauge64 
		MAX-ACCESS read-only 
		STATUS current
		DESCRIPTION  "Stream err" 
		::={ acosSlbSpdyProxyS 22 } 

		slbSpdyProxySessionErr OBJECT-TYPE
		SYNTAX  CounterBasedGauge64 
		MAX-ACCESS read-only 
		STATUS current
		DESCRIPTION  "Session err" 
		::={ acosSlbSpdyProxyS 23 } 

		controlFrame OBJECT-TYPE
		SYNTAX  CounterBasedGauge64 
		MAX-ACCESS read-only 
		STATUS current
		DESCRIPTION  "Control frame received" 
		::={ acosSlbSpdyProxyS 24 } 

		synFrame OBJECT-TYPE
		SYNTAX  CounterBasedGauge64 
		MAX-ACCESS read-only 
		STATUS current
		DESCRIPTION  "SYN stream frame received" 
		::={ acosSlbSpdyProxyS 25 } 

		synReplyFrame OBJECT-TYPE
		SYNTAX  CounterBasedGauge64 
		MAX-ACCESS read-only 
		STATUS current
		DESCRIPTION  "SYN reply frame received" 
		::={ acosSlbSpdyProxyS 26 } 

		headersFrame OBJECT-TYPE
		SYNTAX  CounterBasedGauge64 
		MAX-ACCESS read-only 
		STATUS current
		DESCRIPTION  "Headers frame received" 
		::={ acosSlbSpdyProxyS 27 } 

		settingsFrame OBJECT-TYPE
		SYNTAX  CounterBasedGauge64 
		MAX-ACCESS read-only 
		STATUS current
		DESCRIPTION  "Setting frame received" 
		::={ acosSlbSpdyProxyS 28 } 

		windowFrame OBJECT-TYPE
		SYNTAX  CounterBasedGauge64 
		MAX-ACCESS read-only 
		STATUS current
		DESCRIPTION  "Window update frame received" 
		::={ acosSlbSpdyProxyS 29 } 

		pingFrame OBJECT-TYPE
		SYNTAX  CounterBasedGauge64 
		MAX-ACCESS read-only 
		STATUS current
		DESCRIPTION  "Ping frame received" 
		::={ acosSlbSpdyProxyS 30 } 

		dataFrame OBJECT-TYPE
		SYNTAX  CounterBasedGauge64 
		MAX-ACCESS read-only 
		STATUS current
		DESCRIPTION  "Data frame received" 
		::={ acosSlbSpdyProxyS 31 } 

		dataNoStream OBJECT-TYPE
		SYNTAX  CounterBasedGauge64 
		MAX-ACCESS read-only 
		STATUS current
		DESCRIPTION  "Data no stream found" 
		::={ acosSlbSpdyProxyS 32 } 

		dataNoStreamNoGoaway OBJECT-TYPE
		SYNTAX  CounterBasedGauge64 
		MAX-ACCESS read-only 
		STATUS current
		DESCRIPTION  "Data no stream and no goaway" 
		::={ acosSlbSpdyProxyS 33 } 

		dataNoStreamGoawayClose OBJECT-TYPE
		SYNTAX  CounterBasedGauge64 
		MAX-ACCESS read-only 
		STATUS current
		DESCRIPTION  "Data no stream and no goaway and close session" 
		::={ acosSlbSpdyProxyS 34 } 

		estCbNoTuple OBJECT-TYPE
		SYNTAX  CounterBasedGauge64 
		MAX-ACCESS read-only 
		STATUS current
		DESCRIPTION  "Est callback no tuple" 
		::={ acosSlbSpdyProxyS 35 } 

		dataCbNoTuple OBJECT-TYPE
		SYNTAX  CounterBasedGauge64 
		MAX-ACCESS read-only 
		STATUS current
		DESCRIPTION  "Data callback no tuple" 
		::={ acosSlbSpdyProxyS 36 } 

		ctxAllocFail OBJECT-TYPE
		SYNTAX  CounterBasedGauge64 
		MAX-ACCESS read-only 
		STATUS current
		DESCRIPTION  "Context alloc fail" 
		::={ acosSlbSpdyProxyS 37 } 

		finCloseSession OBJECT-TYPE
		SYNTAX  CounterBasedGauge64 
		MAX-ACCESS read-only 
		STATUS current
		DESCRIPTION  "FIN close session" 
		::={ acosSlbSpdyProxyS 38 } 

		serverRstCloseStream OBJECT-TYPE
		SYNTAX  CounterBasedGauge64 
		MAX-ACCESS read-only 
		STATUS current
		DESCRIPTION  "Server RST close stream" 
		::={ acosSlbSpdyProxyS 39 } 

		streamFound OBJECT-TYPE
		SYNTAX  CounterBasedGauge64 
		MAX-ACCESS read-only 
		STATUS current
		DESCRIPTION  "Stream found" 
		::={ acosSlbSpdyProxyS 40 } 

		closeStreamSessionNotFound OBJECT-TYPE
		SYNTAX  CounterBasedGauge64 
		MAX-ACCESS read-only 
		STATUS current
		DESCRIPTION  "Close stream session not found" 
		::={ acosSlbSpdyProxyS 41 } 

		closeStreamStreamNotFound OBJECT-TYPE
		SYNTAX  CounterBasedGauge64 
		MAX-ACCESS read-only 
		STATUS current
		DESCRIPTION  "Close stream stream not found" 
		::={ acosSlbSpdyProxyS 42 } 

		closeStreamAlreadyClosed OBJECT-TYPE
		SYNTAX  CounterBasedGauge64 
		MAX-ACCESS read-only 
		STATUS current
		DESCRIPTION  "Closing closed stream" 
		::={ acosSlbSpdyProxyS 43 } 

		closeStreamSessionClose OBJECT-TYPE
		SYNTAX  CounterBasedGauge64 
		MAX-ACCESS read-only 
		STATUS current
		DESCRIPTION  "Stream close session close" 
		::={ acosSlbSpdyProxyS 44 } 

		closeSessionAlreadyClosed OBJECT-TYPE
		SYNTAX  CounterBasedGauge64 
		MAX-ACCESS read-only 
		STATUS current
		DESCRIPTION  "Closing closed session" 
		::={ acosSlbSpdyProxyS 45 } 

		maxConcurrentStreamLimit OBJECT-TYPE
		SYNTAX  CounterBasedGauge64 
		MAX-ACCESS read-only 
		STATUS current
		DESCRIPTION  "Max concurrent stream limit" 
		::={ acosSlbSpdyProxyS 46 } 

		streamAllocFail OBJECT-TYPE
		SYNTAX  CounterBasedGauge64 
		MAX-ACCESS read-only 
		STATUS current
		DESCRIPTION  "Stream alloc fail" 
		::={ acosSlbSpdyProxyS 47 } 

		httpConnAllocFail OBJECT-TYPE
		SYNTAX  CounterBasedGauge64 
		MAX-ACCESS read-only 
		STATUS current
		DESCRIPTION  "HTTP connection allocation fail" 
		::={ acosSlbSpdyProxyS 48 } 

		requestHeaderAllocFail OBJECT-TYPE
		SYNTAX  CounterBasedGauge64 
		MAX-ACCESS read-only 
		STATUS current
		DESCRIPTION  "Request/Header allocation fail" 
		::={ acosSlbSpdyProxyS 49 } 

		nameValueTotalLenEx OBJECT-TYPE
		SYNTAX  CounterBasedGauge64 
		MAX-ACCESS read-only 
		STATUS current
		DESCRIPTION  "Name value total length exceeded" 
		::={ acosSlbSpdyProxyS 50 } 

		nameValueZeroLen OBJECT-TYPE
		SYNTAX  CounterBasedGauge64 
		MAX-ACCESS read-only 
		STATUS current
		DESCRIPTION  "Name value zero name length" 
		::={ acosSlbSpdyProxyS 51 } 

		nameValueInvalidHttpVer OBJECT-TYPE
		SYNTAX  CounterBasedGauge64 
		MAX-ACCESS read-only 
		STATUS current
		DESCRIPTION  "Name value invalid http version" 
		::={ acosSlbSpdyProxyS 52 } 

		nameValueConnection OBJECT-TYPE
		SYNTAX  CounterBasedGauge64 
		MAX-ACCESS read-only 
		STATUS current
		DESCRIPTION  "Name value connection" 
		::={ acosSlbSpdyProxyS 53 } 

		nameValueKeepalive OBJECT-TYPE
		SYNTAX  CounterBasedGauge64 
		MAX-ACCESS read-only 
		STATUS current
		DESCRIPTION  "Name value keep alive" 
		::={ acosSlbSpdyProxyS 54 } 

		nameValueProxyConn OBJECT-TYPE
		SYNTAX  CounterBasedGauge64 
		MAX-ACCESS read-only 
		STATUS current
		DESCRIPTION  "Name value proxy-connection" 
		::={ acosSlbSpdyProxyS 55 } 

		nameValueTrasnferEncod OBJECT-TYPE
		SYNTAX  CounterBasedGauge64 
		MAX-ACCESS read-only 
		STATUS current
		DESCRIPTION  "Name value transfer encoding" 
		::={ acosSlbSpdyProxyS 56 } 

		nameValueNoMustHave OBJECT-TYPE
		SYNTAX  CounterBasedGauge64 
		MAX-ACCESS read-only 
		STATUS current
		DESCRIPTION  "Name value no must have" 
		::={ acosSlbSpdyProxyS 57 } 

		decompressFail OBJECT-TYPE
		SYNTAX  CounterBasedGauge64 
		MAX-ACCESS read-only 
		STATUS current
		DESCRIPTION  "Decompress fail" 
		::={ acosSlbSpdyProxyS 58 } 

		synAfterGoaway OBJECT-TYPE
		SYNTAX  CounterBasedGauge64 
		MAX-ACCESS read-only 
		STATUS current
		DESCRIPTION  "SYN after goaway" 
		::={ acosSlbSpdyProxyS 59 } 

		streamLtPrev OBJECT-TYPE
		SYNTAX  CounterBasedGauge64 
		MAX-ACCESS read-only 
		STATUS current
		DESCRIPTION  "Stream id less than previous" 
		::={ acosSlbSpdyProxyS 60 } 

		synStreamExistOrEven OBJECT-TYPE
		SYNTAX  CounterBasedGauge64 
		MAX-ACCESS read-only 
		STATUS current
		DESCRIPTION  "Stream already exists" 
		::={ acosSlbSpdyProxyS 61 } 

		synUnidir OBJECT-TYPE
		SYNTAX  CounterBasedGauge64 
		MAX-ACCESS read-only 
		STATUS current
		DESCRIPTION  "Unidirectional SYN" 
		::={ acosSlbSpdyProxyS 62 } 

		synReplyAlrRcvd OBJECT-TYPE
		SYNTAX  CounterBasedGauge64 
		MAX-ACCESS read-only 
		STATUS current
		DESCRIPTION  "SYN reply already received" 
		::={ acosSlbSpdyProxyS 63 } 

		clientRstNostream OBJECT-TYPE
		SYNTAX  CounterBasedGauge64 
		MAX-ACCESS read-only 
		STATUS current
		DESCRIPTION  "Close RST stream not found" 
		::={ acosSlbSpdyProxyS 64 } 

		windowNoStream OBJECT-TYPE
		SYNTAX  CounterBasedGauge64 
		MAX-ACCESS read-only 
		STATUS current
		DESCRIPTION  "Window update no stream found" 
		::={ acosSlbSpdyProxyS 65 } 

		invalidWindowSize OBJECT-TYPE
		SYNTAX  CounterBasedGauge64 
		MAX-ACCESS read-only 
		STATUS current
		DESCRIPTION  "Invalid window size" 
		::={ acosSlbSpdyProxyS 66 } 

		unknownControlFrame OBJECT-TYPE
		SYNTAX  CounterBasedGauge64 
		MAX-ACCESS read-only 
		STATUS current
		DESCRIPTION  "Unknown control frame" 
		::={ acosSlbSpdyProxyS 67 } 

		dataOnClosedStream OBJECT-TYPE
		SYNTAX  CounterBasedGauge64 
		MAX-ACCESS read-only 
		STATUS current
		DESCRIPTION  "Data on closed stream" 
		::={ acosSlbSpdyProxyS 68 } 

		invalidFrameSize OBJECT-TYPE
		SYNTAX  CounterBasedGauge64 
		MAX-ACCESS read-only 
		STATUS current
		DESCRIPTION  "Invalid frame size" 
		::={ acosSlbSpdyProxyS 69 } 

		invalidVersion OBJECT-TYPE
		SYNTAX  CounterBasedGauge64 
		MAX-ACCESS read-only 
		STATUS current
		DESCRIPTION  "Invalid version" 
		::={ acosSlbSpdyProxyS 70 } 

		headerAfterSessionClose OBJECT-TYPE
		SYNTAX  CounterBasedGauge64 
		MAX-ACCESS read-only 
		STATUS current
		DESCRIPTION  "Header after session close" 
		::={ acosSlbSpdyProxyS 71 } 

		compressCtxAllocFail OBJECT-TYPE
		SYNTAX  CounterBasedGauge64 
		MAX-ACCESS read-only 
		STATUS current
		DESCRIPTION  "Compression context allocation fail" 
		::={ acosSlbSpdyProxyS 72 } 

		headerCompressFail OBJECT-TYPE
		SYNTAX  CounterBasedGauge64 
		MAX-ACCESS read-only 
		STATUS current
		DESCRIPTION  "Header compress fail" 
		::={ acosSlbSpdyProxyS 73 } 

		httpDataSessionClose OBJECT-TYPE
		SYNTAX  CounterBasedGauge64 
		MAX-ACCESS read-only 
		STATUS current
		DESCRIPTION  "HTTP data session close" 
		::={ acosSlbSpdyProxyS 74 } 

		httpDataStreamNotFound OBJECT-TYPE
		SYNTAX  CounterBasedGauge64 
		MAX-ACCESS read-only 
		STATUS current
		DESCRIPTION  "HTTP data stream not found" 
		::={ acosSlbSpdyProxyS 75 } 

		closeStreamNotHttpProxy OBJECT-TYPE
		SYNTAX  CounterBasedGauge64 
		MAX-ACCESS read-only 
		STATUS current
		DESCRIPTION  "Close Stream not http-proxy" 
		::={ acosSlbSpdyProxyS 76 } 

		sessionNeedsRequeue OBJECT-TYPE
		SYNTAX  CounterBasedGauge64 
		MAX-ACCESS read-only 
		STATUS current
		DESCRIPTION  "Session needs requeue" 
		::={ acosSlbSpdyProxyS 77 } 

		newStreamSessionDel OBJECT-TYPE
		SYNTAX  CounterBasedGauge64 
		MAX-ACCESS read-only 
		STATUS current
		DESCRIPTION  "New Stream after Session delete" 
		::={ acosSlbSpdyProxyS 78 } 

		finStreamClosed OBJECT-TYPE
		SYNTAX  CounterBasedGauge64 
		MAX-ACCESS read-only 
		STATUS current
		DESCRIPTION  "HTTP FIN stream already closed" 
		::={ acosSlbSpdyProxyS 79 } 

		httpCloseStreamClosed OBJECT-TYPE
		SYNTAX  CounterBasedGauge64 
		MAX-ACCESS read-only 
		STATUS current
		DESCRIPTION  "HTTP close stream already closed" 
		::={ acosSlbSpdyProxyS 80 } 

		httpErrStreamClosed OBJECT-TYPE
		SYNTAX  CounterBasedGauge64 
		MAX-ACCESS read-only 
		STATUS current
		DESCRIPTION  "HTTP error stream already closed" 
		::={ acosSlbSpdyProxyS 81 } 

		httpHdrStreamClose OBJECT-TYPE
		SYNTAX  CounterBasedGauge64 
		MAX-ACCESS read-only 
		STATUS current
		DESCRIPTION  "HTTP header stream already closed" 
		::={ acosSlbSpdyProxyS 82 } 

		httpDataStreamClose OBJECT-TYPE
		SYNTAX  CounterBasedGauge64 
		MAX-ACCESS read-only 
		STATUS current
		DESCRIPTION  "HTTP data stream already closed" 
		::={ acosSlbSpdyProxyS 83 } 

		sessionClose OBJECT-TYPE
		SYNTAX  CounterBasedGauge64 
		MAX-ACCESS read-only 
		STATUS current
		DESCRIPTION  "Session close" 
		::={ acosSlbSpdyProxyS 84 } 

acosSlbHttp2                        OBJECT IDENTIFIER ::= { acosSlb 63 }
acosSlbHttp2S                       OBJECT IDENTIFIER ::= { acosSlbHttp2 1 }

		slbHttp2CurrProxy OBJECT-TYPE
		SYNTAX  CounterBasedGauge64 
		MAX-ACCESS read-only 
		STATUS current
		DESCRIPTION  "Curr Proxy Conns" 
		::={ acosSlbHttp2S 1 } 

		slbHttp2TotalProxy OBJECT-TYPE
		SYNTAX  CounterBasedGauge64 
		MAX-ACCESS read-only 
		STATUS current
		DESCRIPTION  "Total Proxy Conns" 
		::={ acosSlbHttp2S 2 } 

		connectionPrefaceRcvd OBJECT-TYPE
		SYNTAX  CounterBasedGauge64 
		MAX-ACCESS read-only 
		STATUS current
		DESCRIPTION  "Connection preface rcvd" 
		::={ acosSlbHttp2S 3 } 

		controlFrame OBJECT-TYPE
		SYNTAX  CounterBasedGauge64 
		MAX-ACCESS read-only 
		STATUS current
		DESCRIPTION  "Control Frame Rcvd" 
		::={ acosSlbHttp2S 4 } 

		headersFrame OBJECT-TYPE
		SYNTAX  CounterBasedGauge64 
		MAX-ACCESS read-only 
		STATUS current
		DESCRIPTION  "HEADERS Frame Rcvd" 
		::={ acosSlbHttp2S 5 } 

		continuationFrame OBJECT-TYPE
		SYNTAX  CounterBasedGauge64 
		MAX-ACCESS read-only 
		STATUS current
		DESCRIPTION  "CONTINUATION Frame Rcvd" 
		::={ acosSlbHttp2S 6 } 

		rstFrameRcvd OBJECT-TYPE
		SYNTAX  CounterBasedGauge64 
		MAX-ACCESS read-only 
		STATUS current
		DESCRIPTION  "RST_STREAM Frame Rcvd" 
		::={ acosSlbHttp2S 7 } 

		settingsFrame OBJECT-TYPE
		SYNTAX  CounterBasedGauge64 
		MAX-ACCESS read-only 
		STATUS current
		DESCRIPTION  "SETTINGS Frame Rcvd" 
		::={ acosSlbHttp2S 8 } 

		windowUpdateFrame OBJECT-TYPE
		SYNTAX  CounterBasedGauge64 
		MAX-ACCESS read-only 
		STATUS current
		DESCRIPTION  "WINDOW_UPDATE Frame Rcvd" 
		::={ acosSlbHttp2S 9 } 

		pingFrame OBJECT-TYPE
		SYNTAX  CounterBasedGauge64 
		MAX-ACCESS read-only 
		STATUS current
		DESCRIPTION  "PING Frame Rcvd" 
		::={ acosSlbHttp2S 10 } 

		goawayFrame OBJECT-TYPE
		SYNTAX  CounterBasedGauge64 
		MAX-ACCESS read-only 
		STATUS current
		DESCRIPTION  "GOAWAY Frame Rcvd" 
		::={ acosSlbHttp2S 11 } 

		priorityFrame OBJECT-TYPE
		SYNTAX  CounterBasedGauge64 
		MAX-ACCESS read-only 
		STATUS current
		DESCRIPTION  "PRIORITY Frame Rcvd" 
		::={ acosSlbHttp2S 12 } 

		dataFrame OBJECT-TYPE
		SYNTAX  CounterBasedGauge64 
		MAX-ACCESS read-only 
		STATUS current
		DESCRIPTION  "DATA Frame Recvd" 
		::={ acosSlbHttp2S 13 } 

		unknownFrame OBJECT-TYPE
		SYNTAX  CounterBasedGauge64 
		MAX-ACCESS read-only 
		STATUS current
		DESCRIPTION  "Unknown Frame Recvd" 
		::={ acosSlbHttp2S 14 } 

		connectionPrefaceSent OBJECT-TYPE
		SYNTAX  CounterBasedGauge64 
		MAX-ACCESS read-only 
		STATUS current
		DESCRIPTION  "Connection preface sent" 
		::={ acosSlbHttp2S 15 } 

		settingsFrameSent OBJECT-TYPE
		SYNTAX  CounterBasedGauge64 
		MAX-ACCESS read-only 
		STATUS current
		DESCRIPTION  "SETTINGS Frame Sent" 
		::={ acosSlbHttp2S 16 } 

		settingsAckSent OBJECT-TYPE
		SYNTAX  CounterBasedGauge64 
		MAX-ACCESS read-only 
		STATUS current
		DESCRIPTION  "SETTINGS ACK Frame Sent" 
		::={ acosSlbHttp2S 17 } 

		emptySettingsSent OBJECT-TYPE
		SYNTAX  CounterBasedGauge64 
		MAX-ACCESS read-only 
		STATUS current
		DESCRIPTION  "Empty SETTINGS Frame Sent" 
		::={ acosSlbHttp2S 18 } 

		pingFrameSent OBJECT-TYPE
		SYNTAX  CounterBasedGauge64 
		MAX-ACCESS read-only 
		STATUS current
		DESCRIPTION  "PING Frame Sent" 
		::={ acosSlbHttp2S 19 } 

		windowUpdateFrameSent OBJECT-TYPE
		SYNTAX  CounterBasedGauge64 
		MAX-ACCESS read-only 
		STATUS current
		DESCRIPTION  "WINDOW_UPDATE Frame Sent" 
		::={ acosSlbHttp2S 20 } 

		rstFrameSent OBJECT-TYPE
		SYNTAX  CounterBasedGauge64 
		MAX-ACCESS read-only 
		STATUS current
		DESCRIPTION  "RST_STREAM Frame Sent" 
		::={ acosSlbHttp2S 21 } 

		goawayFrameSent OBJECT-TYPE
		SYNTAX  CounterBasedGauge64 
		MAX-ACCESS read-only 
		STATUS current
		DESCRIPTION  "GOAWAY Frame Sent" 
		::={ acosSlbHttp2S 22 } 

		headerToApp OBJECT-TYPE
		SYNTAX  CounterBasedGauge64 
		MAX-ACCESS read-only 
		STATUS current
		DESCRIPTION  "HEADER Frame to HTTP" 
		::={ acosSlbHttp2S 23 } 

		dataToApp OBJECT-TYPE
		SYNTAX  CounterBasedGauge64 
		MAX-ACCESS read-only 
		STATUS current
		DESCRIPTION  "DATA Frame to HTTP" 
		::={ acosSlbHttp2S 24 } 

		protocolError OBJECT-TYPE
		SYNTAX  CounterBasedGauge64 
		MAX-ACCESS read-only 
		STATUS current
		DESCRIPTION  "Protocol Error" 
		::={ acosSlbHttp2S 25 } 

		internalError OBJECT-TYPE
		SYNTAX  CounterBasedGauge64 
		MAX-ACCESS read-only 
		STATUS current
		DESCRIPTION  "Internal Error" 
		::={ acosSlbHttp2S 26 } 

		proxyAllocError OBJECT-TYPE
		SYNTAX  CounterBasedGauge64 
		MAX-ACCESS read-only 
		STATUS current
		DESCRIPTION  "HTTP2 Proxy alloc Error" 
		::={ acosSlbHttp2S 27 } 

		splitBuffFail OBJECT-TYPE
		SYNTAX  CounterBasedGauge64 
		MAX-ACCESS read-only 
		STATUS current
		DESCRIPTION  "Splitting Buffer Failed" 
		::={ acosSlbHttp2S 28 } 

		invalidFrameSize OBJECT-TYPE
		SYNTAX  CounterBasedGauge64 
		MAX-ACCESS read-only 
		STATUS current
		DESCRIPTION  "Invalid Frame Size Rcvd" 
		::={ acosSlbHttp2S 29 } 

		errorMaxInvalidStream OBJECT-TYPE
		SYNTAX  CounterBasedGauge64 
		MAX-ACCESS read-only 
		STATUS current
		DESCRIPTION  "Max Invalid Stream Rcvd" 
		::={ acosSlbHttp2S 31 } 

		dataNoStream OBJECT-TYPE
		SYNTAX  CounterBasedGauge64 
		MAX-ACCESS read-only 
		STATUS current
		DESCRIPTION  "DATA Frame Rcvd on non-existent stream" 
		::={ acosSlbHttp2S 32 } 

		flowControlError OBJECT-TYPE
		SYNTAX  CounterBasedGauge64 
		MAX-ACCESS read-only 
		STATUS current
		DESCRIPTION  "Flow Control Error" 
		::={ acosSlbHttp2S 33 } 

		settingsTimeout OBJECT-TYPE
		SYNTAX  CounterBasedGauge64 
		MAX-ACCESS read-only 
		STATUS current
		DESCRIPTION  "Settings Timeout" 
		::={ acosSlbHttp2S 34 } 

		frameSizeError OBJECT-TYPE
		SYNTAX  CounterBasedGauge64 
		MAX-ACCESS read-only 
		STATUS current
		DESCRIPTION  "Frame Size Error" 
		::={ acosSlbHttp2S 35 } 

		refusedStream OBJECT-TYPE
		SYNTAX  CounterBasedGauge64 
		MAX-ACCESS read-only 
		STATUS current
		DESCRIPTION  "Refused Stream" 
		::={ acosSlbHttp2S 36 } 

		cancel OBJECT-TYPE
		SYNTAX  CounterBasedGauge64 
		MAX-ACCESS read-only 
		STATUS current
		DESCRIPTION  "cancel" 
		::={ acosSlbHttp2S 37 } 

		compressionError OBJECT-TYPE
		SYNTAX  CounterBasedGauge64 
		MAX-ACCESS read-only 
		STATUS current
		DESCRIPTION  "compression error" 
		::={ acosSlbHttp2S 38 } 

		connectError OBJECT-TYPE
		SYNTAX  CounterBasedGauge64 
		MAX-ACCESS read-only 
		STATUS current
		DESCRIPTION  "connect error" 
		::={ acosSlbHttp2S 39 } 

		enhanceYourCalm OBJECT-TYPE
		SYNTAX  CounterBasedGauge64 
		MAX-ACCESS read-only 
		STATUS current
		DESCRIPTION  "enhance your calm error" 
		::={ acosSlbHttp2S 40 } 

		inadequateSecurity OBJECT-TYPE
		SYNTAX  CounterBasedGauge64 
		MAX-ACCESS read-only 
		STATUS current
		DESCRIPTION  "inadequate security" 
		::={ acosSlbHttp2S 41 } 

		http11Required OBJECT-TYPE
		SYNTAX  CounterBasedGauge64 
		MAX-ACCESS read-only 
		STATUS current
		DESCRIPTION  "HTTP1.1 Required" 
		::={ acosSlbHttp2S 42 } 

		deflateAllocFail OBJECT-TYPE
		SYNTAX  CounterBasedGauge64 
		MAX-ACCESS read-only 
		STATUS current
		DESCRIPTION  "deflate alloc fail" 
		::={ acosSlbHttp2S 43 } 

		inflateAllocFail OBJECT-TYPE
		SYNTAX  CounterBasedGauge64 
		MAX-ACCESS read-only 
		STATUS current
		DESCRIPTION  "inflate alloc fail" 
		::={ acosSlbHttp2S 44 } 

		inflateHeaderFail OBJECT-TYPE
		SYNTAX  CounterBasedGauge64 
		MAX-ACCESS read-only 
		STATUS current
		DESCRIPTION  "Inflate Header Fail" 
		::={ acosSlbHttp2S 45 } 

		badConnectionPreface OBJECT-TYPE
		SYNTAX  CounterBasedGauge64 
		MAX-ACCESS read-only 
		STATUS current
		DESCRIPTION  "Bad Connection Preface" 
		::={ acosSlbHttp2S 46 } 

		cantAllocateControlFrame OBJECT-TYPE
		SYNTAX  CounterBasedGauge64 
		MAX-ACCESS read-only 
		STATUS current
		DESCRIPTION  "Cant allocate control frame" 
		::={ acosSlbHttp2S 47 } 

		cantAllocateSettingsFrame OBJECT-TYPE
		SYNTAX  CounterBasedGauge64 
		MAX-ACCESS read-only 
		STATUS current
		DESCRIPTION  "Cant allocate SETTINGS frame" 
		::={ acosSlbHttp2S 48 } 

		badFrameTypeForStreamState OBJECT-TYPE
		SYNTAX  CounterBasedGauge64 
		MAX-ACCESS read-only 
		STATUS current
		DESCRIPTION  "Bad frame type for stream state" 
		::={ acosSlbHttp2S 49 } 

		wrongStreamState OBJECT-TYPE
		SYNTAX  CounterBasedGauge64 
		MAX-ACCESS read-only 
		STATUS current
		DESCRIPTION  "Wrong Stream State" 
		::={ acosSlbHttp2S 50 } 

		dataQueueAllocError OBJECT-TYPE
		SYNTAX  CounterBasedGauge64 
		MAX-ACCESS read-only 
		STATUS current
		DESCRIPTION  "Data Queue Alloc Error" 
		::={ acosSlbHttp2S 51 } 

		buffAllocError OBJECT-TYPE
		SYNTAX  CounterBasedGauge64 
		MAX-ACCESS read-only 
		STATUS current
		DESCRIPTION  "Buff alloc error" 
		::={ acosSlbHttp2S 52 } 

		cantAllocateRstFrame OBJECT-TYPE
		SYNTAX  CounterBasedGauge64 
		MAX-ACCESS read-only 
		STATUS current
		DESCRIPTION  "Cant allocate RST_STREAM frame" 
		::={ acosSlbHttp2S 53 } 

		cantAllocateGoawayFrame OBJECT-TYPE
		SYNTAX  CounterBasedGauge64 
		MAX-ACCESS read-only 
		STATUS current
		DESCRIPTION  "Cant allocate GOAWAY frame" 
		::={ acosSlbHttp2S 54 } 

		cantAllocatePingFrame OBJECT-TYPE
		SYNTAX  CounterBasedGauge64 
		MAX-ACCESS read-only 
		STATUS current
		DESCRIPTION  "Cant allocate PING frame" 
		::={ acosSlbHttp2S 55 } 

		cantAllocateStream OBJECT-TYPE
		SYNTAX  CounterBasedGauge64 
		MAX-ACCESS read-only 
		STATUS current
		DESCRIPTION  "Cant allocate stream" 
		::={ acosSlbHttp2S 56 } 

		cantAllocateWindowFrame OBJECT-TYPE
		SYNTAX  CounterBasedGauge64 
		MAX-ACCESS read-only 
		STATUS current
		DESCRIPTION  "Cant allocate WINDOW_UPDATE frame" 
		::={ acosSlbHttp2S 57 } 

		headerNoStream OBJECT-TYPE
		SYNTAX  CounterBasedGauge64 
		MAX-ACCESS read-only 
		STATUS current
		DESCRIPTION  "header no stream" 
		::={ acosSlbHttp2S 58 } 

		headerPadlenGtFramePayload OBJECT-TYPE
		SYNTAX  CounterBasedGauge64 
		MAX-ACCESS read-only 
		STATUS current
		DESCRIPTION  "Header padlen greater than frame payload size" 
		::={ acosSlbHttp2S 59 } 

		streamsGtMaxConcurStreams OBJECT-TYPE
		SYNTAX  CounterBasedGauge64 
		MAX-ACCESS read-only 
		STATUS current
		DESCRIPTION  "Streams greater than max allowed concurrent streams" 
		::={ acosSlbHttp2S 60 } 

		idleStateUnexpectedFrame OBJECT-TYPE
		SYNTAX  CounterBasedGauge64 
		MAX-ACCESS read-only 
		STATUS current
		DESCRIPTION  "Unxpected frame received in idle state" 
		::={ acosSlbHttp2S 61 } 

		reservedLocalStateUnexpectedFrame OBJECT-TYPE
		SYNTAX  CounterBasedGauge64 
		MAX-ACCESS read-only 
		STATUS current
		DESCRIPTION  "Unexpected frame received in reserved local state" 
		::={ acosSlbHttp2S 62 } 

		reservedRemoteStateUnexpectedFrame OBJECT-TYPE
		SYNTAX  CounterBasedGauge64 
		MAX-ACCESS read-only 
		STATUS current
		DESCRIPTION  "Unexpected frame received in reserved remote state" 
		::={ acosSlbHttp2S 63 } 

		halfClosedRemoteStateUnexpectedFrame OBJECT-TYPE
		SYNTAX  CounterBasedGauge64 
		MAX-ACCESS read-only 
		STATUS current
		DESCRIPTION  "Unexpected frame received in half closed remote state" 
		::={ acosSlbHttp2S 64 } 

		closedStateUnexpectedFrame OBJECT-TYPE
		SYNTAX  CounterBasedGauge64 
		MAX-ACCESS read-only 
		STATUS current
		DESCRIPTION  "Unexpected frame received in closed state" 
		::={ acosSlbHttp2S 65 } 

		zeroWindowSizeOnStream OBJECT-TYPE
		SYNTAX  CounterBasedGauge64 
		MAX-ACCESS read-only 
		STATUS current
		DESCRIPTION  "Window Update with zero increment rcvd" 
		::={ acosSlbHttp2S 66 } 

		exceedsMaxWindowSizeStream OBJECT-TYPE
		SYNTAX  CounterBasedGauge64 
		MAX-ACCESS read-only 
		STATUS current
		DESCRIPTION  "Window Update with increment that results in exceeding max window" 
		::={ acosSlbHttp2S 68 } 

		streamClosed OBJECT-TYPE
		SYNTAX  CounterBasedGauge64 
		MAX-ACCESS read-only 
		STATUS current
		DESCRIPTION  "stream closed" 
		::={ acosSlbHttp2S 70 } 

		continuationBeforeHeaders OBJECT-TYPE
		SYNTAX  CounterBasedGauge64 
		MAX-ACCESS read-only 
		STATUS current
		DESCRIPTION  "CONTINUATION frame with no headers frame" 
		::={ acosSlbHttp2S 71 } 

		invalidFrameDuringHeaders OBJECT-TYPE
		SYNTAX  CounterBasedGauge64 
		MAX-ACCESS read-only 
		STATUS current
		DESCRIPTION  "frame before headers were complete" 
		::={ acosSlbHttp2S 72 } 

		headersAfterContinuation OBJECT-TYPE
		SYNTAX  CounterBasedGauge64 
		MAX-ACCESS read-only 
		STATUS current
		DESCRIPTION  "headers frame before CONTINUATION was complete" 
		::={ acosSlbHttp2S 73 } 

		pushPromiseFrameSent OBJECT-TYPE
		SYNTAX  CounterBasedGauge64 
		MAX-ACCESS read-only 
		STATUS current
		DESCRIPTION  "Push Promise Frame Sent" 
		::={ acosSlbHttp2S 114 } 

		invalidPushPromise OBJECT-TYPE
		SYNTAX  CounterBasedGauge64 
		MAX-ACCESS read-only 
		STATUS current
		DESCRIPTION  "unexpected PUSH_PROMISE frame" 
		::={ acosSlbHttp2S 74 } 

		invalidStreamId OBJECT-TYPE
		SYNTAX  CounterBasedGauge64 
		MAX-ACCESS read-only 
		STATUS current
		DESCRIPTION  "received invalid stream ID" 
		::={ acosSlbHttp2S 75 } 

		headersInterleaved OBJECT-TYPE
		SYNTAX  CounterBasedGauge64 
		MAX-ACCESS read-only 
		STATUS current
		DESCRIPTION  "headers interleaved on streams" 
		::={ acosSlbHttp2S 76 } 

		trailersNoEndStream OBJECT-TYPE
		SYNTAX  CounterBasedGauge64 
		MAX-ACCESS read-only 
		STATUS current
		DESCRIPTION  "trailers not marked as end-of-stream" 
		::={ acosSlbHttp2S 77 } 

		invalidSettingValue OBJECT-TYPE
		SYNTAX  CounterBasedGauge64 
		MAX-ACCESS read-only 
		STATUS current
		DESCRIPTION  "invalid setting-frame value" 
		::={ acosSlbHttp2S 78 } 

		invalidWindowUpdate OBJECT-TYPE
		SYNTAX  CounterBasedGauge64 
		MAX-ACCESS read-only 
		STATUS current
		DESCRIPTION  "window-update value out of range" 
		::={ acosSlbHttp2S 79 } 

		frameHeaderBytesReceived OBJECT-TYPE
		SYNTAX  CounterBasedGauge64 
		MAX-ACCESS read-only 
		STATUS current
		DESCRIPTION  "frame header bytes received" 
		::={ acosSlbHttp2S 80 } 

		frameHeaderBytesSent OBJECT-TYPE
		SYNTAX  CounterBasedGauge64 
		MAX-ACCESS read-only 
		STATUS current
		DESCRIPTION  "frame header bytes sent" 
		::={ acosSlbHttp2S 81 } 

		controlBytesReceived OBJECT-TYPE
		SYNTAX  CounterBasedGauge64 
		MAX-ACCESS read-only 
		STATUS current
		DESCRIPTION  "HTTP/2 control frame bytes received" 
		::={ acosSlbHttp2S 82 } 

		controlBytesSent OBJECT-TYPE
		SYNTAX  CounterBasedGauge64 
		MAX-ACCESS read-only 
		STATUS current
		DESCRIPTION  "HTTP/2 control frame bytes sent" 
		::={ acosSlbHttp2S 83 } 

		headerBytesReceived OBJECT-TYPE
		SYNTAX  CounterBasedGauge64 
		MAX-ACCESS read-only 
		STATUS current
		DESCRIPTION  "HTTP/2 header bytes received" 
		::={ acosSlbHttp2S 84 } 

		headerBytesSent OBJECT-TYPE
		SYNTAX  CounterBasedGauge64 
		MAX-ACCESS read-only 
		STATUS current
		DESCRIPTION  "HTTP/2 header bytes sent" 
		::={ acosSlbHttp2S 85 } 

		dataBytesReceived OBJECT-TYPE
		SYNTAX  CounterBasedGauge64 
		MAX-ACCESS read-only 
		STATUS current
		DESCRIPTION  "HTTP/2 data bytes received" 
		::={ acosSlbHttp2S 86 } 

		dataBytesSent OBJECT-TYPE
		SYNTAX  CounterBasedGauge64 
		MAX-ACCESS read-only 
		STATUS current
		DESCRIPTION  "HTTP/2 data bytes sent" 
		::={ acosSlbHttp2S 87 } 

		totalBytesReceived OBJECT-TYPE
		SYNTAX  CounterBasedGauge64 
		MAX-ACCESS read-only 
		STATUS current
		DESCRIPTION  "HTTP/2 total bytes received" 
		::={ acosSlbHttp2S 88 } 

		totalBytesSent OBJECT-TYPE
		SYNTAX  CounterBasedGauge64 
		MAX-ACCESS read-only 
		STATUS current
		DESCRIPTION  "HTTP/2 total bytes sent" 
		::={ acosSlbHttp2S 89 } 

		slbHttp2PeakProxy OBJECT-TYPE
		SYNTAX  CounterBasedGauge64 
		MAX-ACCESS read-only 
		STATUS current
		DESCRIPTION  "Peak Proxy Conns" 
		::={ acosSlbHttp2S 90 } 

		controlFrameSent OBJECT-TYPE
		SYNTAX  CounterBasedGauge64 
		MAX-ACCESS read-only 
		STATUS current
		DESCRIPTION  "Control Frame Sent" 
		::={ acosSlbHttp2S 91 } 

		continuationFrameSent OBJECT-TYPE
		SYNTAX  CounterBasedGauge64 
		MAX-ACCESS read-only 
		STATUS current
		DESCRIPTION  "CONTINUATION Frame Sent" 
		::={ acosSlbHttp2S 92 } 

		dataFrameSent OBJECT-TYPE
		SYNTAX  CounterBasedGauge64 
		MAX-ACCESS read-only 
		STATUS current
		DESCRIPTION  "DATA Frame Sent" 
		::={ acosSlbHttp2S 93 } 

		headersFrameSent OBJECT-TYPE
		SYNTAX  CounterBasedGauge64 
		MAX-ACCESS read-only 
		STATUS current
		DESCRIPTION  "HEADERS Frame Sent" 
		::={ acosSlbHttp2S 94 } 

		priorityFrameSent OBJECT-TYPE
		SYNTAX  CounterBasedGauge64 
		MAX-ACCESS read-only 
		STATUS current
		DESCRIPTION  "PRIORITY Frame Sent" 
		::={ acosSlbHttp2S 95 } 

		settingsAckRcvd OBJECT-TYPE
		SYNTAX  CounterBasedGauge64 
		MAX-ACCESS read-only 
		STATUS current
		DESCRIPTION  "SETTINGS ACK Frame Rcvd" 
		::={ acosSlbHttp2S 96 } 

		emptySettingsRcvd OBJECT-TYPE
		SYNTAX  CounterBasedGauge64 
		MAX-ACCESS read-only 
		STATUS current
		DESCRIPTION  "Empty SETTINGS Frame Rcvd" 
		::={ acosSlbHttp2S 97 } 

		allocFailTotal OBJECT-TYPE
		SYNTAX  CounterBasedGauge64 
		MAX-ACCESS read-only 
		STATUS current
		DESCRIPTION  "Alloc Fail - Total" 
		::={ acosSlbHttp2S 98 } 

		errRcvdTotal OBJECT-TYPE
		SYNTAX  CounterBasedGauge64 
		MAX-ACCESS read-only 
		STATUS current
		DESCRIPTION  "Error Rcvd - Total" 
		::={ acosSlbHttp2S 99 } 

		errSentTotal OBJECT-TYPE
		SYNTAX  CounterBasedGauge64 
		MAX-ACCESS read-only 
		STATUS current
		DESCRIPTION  "Error Rent - Total" 
		::={ acosSlbHttp2S 100 } 

		errSentProtoErr OBJECT-TYPE
		SYNTAX  CounterBasedGauge64 
		MAX-ACCESS read-only 
		STATUS current
		DESCRIPTION  "Error Sent - PROTOCOL_ERROR" 
		::={ acosSlbHttp2S 101 } 

		errSentInternalErr OBJECT-TYPE
		SYNTAX  CounterBasedGauge64 
		MAX-ACCESS read-only 
		STATUS current
		DESCRIPTION  "Error Sent - INTERNAL_ERROR" 
		::={ acosSlbHttp2S 102 } 

		errSentFlowControl OBJECT-TYPE
		SYNTAX  CounterBasedGauge64 
		MAX-ACCESS read-only 
		STATUS current
		DESCRIPTION  "Error Sent - FLOW_CONTROL_ERROR" 
		::={ acosSlbHttp2S 103 } 

		errSentSettingTimeout OBJECT-TYPE
		SYNTAX  CounterBasedGauge64 
		MAX-ACCESS read-only 
		STATUS current
		DESCRIPTION  "Error Sent - SETTINGS_TIMEOUT" 
		::={ acosSlbHttp2S 104 } 

		errSentStreamClosed OBJECT-TYPE
		SYNTAX  CounterBasedGauge64 
		MAX-ACCESS read-only 
		STATUS current
		DESCRIPTION  "Error Sent - STREAM_CLOSED" 
		::={ acosSlbHttp2S 105 } 

		errSentFrameSizeErr OBJECT-TYPE
		SYNTAX  CounterBasedGauge64 
		MAX-ACCESS read-only 
		STATUS current
		DESCRIPTION  "Error Sent - FRAME_SIZE_ERROR" 
		::={ acosSlbHttp2S 106 } 

		errSentRefusedStream OBJECT-TYPE
		SYNTAX  CounterBasedGauge64 
		MAX-ACCESS read-only 
		STATUS current
		DESCRIPTION  "Error Sent - REFUSED_STREAM" 
		::={ acosSlbHttp2S 107 } 

		errSentCancel OBJECT-TYPE
		SYNTAX  CounterBasedGauge64 
		MAX-ACCESS read-only 
		STATUS current
		DESCRIPTION  "Error Sent - CANCEL" 
		::={ acosSlbHttp2S 108 } 

		errSentCompressionErr OBJECT-TYPE
		SYNTAX  CounterBasedGauge64 
		MAX-ACCESS read-only 
		STATUS current
		DESCRIPTION  "Error Sent - COMPRESSION_ERROR" 
		::={ acosSlbHttp2S 109 } 

		errSentConnectErr OBJECT-TYPE
		SYNTAX  CounterBasedGauge64 
		MAX-ACCESS read-only 
		STATUS current
		DESCRIPTION  "Error Sent - CONNECT_ERROR" 
		::={ acosSlbHttp2S 110 } 

		errSentYourCalm OBJECT-TYPE
		SYNTAX  CounterBasedGauge64 
		MAX-ACCESS read-only 
		STATUS current
		DESCRIPTION  "Error Sent - ENHANCE_YOUR_CALM" 
		::={ acosSlbHttp2S 111 } 

		errSentInadequateSecurity OBJECT-TYPE
		SYNTAX  CounterBasedGauge64 
		MAX-ACCESS read-only 
		STATUS current
		DESCRIPTION  "Error Sent - INADEQUATE_SECURITY" 
		::={ acosSlbHttp2S 112 } 

		errSentHttp11Required OBJECT-TYPE
		SYNTAX  CounterBasedGauge64 
		MAX-ACCESS read-only 
		STATUS current
		DESCRIPTION  "Error Sent - HTTP_1_1_REQUIRED" 
		::={ acosSlbHttp2S 113 } 

		http2Rejected OBJECT-TYPE
		SYNTAX  CounterBasedGauge64 
		MAX-ACCESS read-only 
		STATUS current
		DESCRIPTION  "HTTP2 Rejected" 
		::={ acosSlbHttp2S 115 } 

		currentStream OBJECT-TYPE
		SYNTAX  CounterBasedGauge64 
		MAX-ACCESS read-only 
		STATUS current
		DESCRIPTION  "Current Streams" 
		::={ acosSlbHttp2S 116 } 

		streamCreate OBJECT-TYPE
		SYNTAX  CounterBasedGauge64 
		MAX-ACCESS read-only 
		STATUS current
		DESCRIPTION  "Stream Create" 
		::={ acosSlbHttp2S 117 } 

		streamFree OBJECT-TYPE
		SYNTAX  CounterBasedGauge64 
		MAX-ACCESS read-only 
		STATUS current
		DESCRIPTION  "Stream Free" 
		::={ acosSlbHttp2S 118 } 

		endStreamRcvd OBJECT-TYPE
		SYNTAX  CounterBasedGauge64 
		MAX-ACCESS read-only 
		STATUS current
		DESCRIPTION  "End Stream Recieved" 
		::={ acosSlbHttp2S 119 } 

		endStreamSent OBJECT-TYPE
		SYNTAX  CounterBasedGauge64 
		MAX-ACCESS read-only 
		STATUS current
		DESCRIPTION  "End Stream Sent" 
		::={ acosSlbHttp2S 120 } 

		transactionLimited OBJECT-TYPE
		SYNTAX  CounterBasedGauge64 
		MAX-ACCESS read-only 
		STATUS current
		DESCRIPTION  "transaction_limited" 
		::={ acosSlbHttp2S 121 } 

		frameFloodDetected OBJECT-TYPE
		SYNTAX  CounterBasedGauge64 
		MAX-ACCESS read-only 
		STATUS current
		DESCRIPTION  "frame flood detected" 
		::={ acosSlbHttp2S 122 } 

		streamCancelFloodDetected OBJECT-TYPE
		SYNTAX  CounterBasedGauge64 
		MAX-ACCESS read-only 
		STATUS current
		DESCRIPTION  "stream cancel flood detected" 
		::={ acosSlbHttp2S 123 } 

acosSlbHttp3                        OBJECT IDENTIFIER ::= { acosSlb 107 }
acosSlbHttp3S                       OBJECT IDENTIFIER ::= { acosSlbHttp3 1 }

		slbHttp3ClientConnCurr OBJECT-TYPE
		SYNTAX  CounterBasedGauge64 
		MAX-ACCESS read-only 
		STATUS current
		DESCRIPTION  "Current HTTP/3 Client Connections" 
		::={ acosSlbHttp3S 1 } 

		slbHttp3ServerConnCurr OBJECT-TYPE
		SYNTAX  CounterBasedGauge64 
		MAX-ACCESS read-only 
		STATUS current
		DESCRIPTION  "Current HTTP/3 Server Connections" 
		::={ acosSlbHttp3S 2 } 

		slbHttp3ClientConnTotal OBJECT-TYPE
		SYNTAX  CounterBasedGauge64 
		MAX-ACCESS read-only 
		STATUS current
		DESCRIPTION  "Total HTTP/3 Client Connections" 
		::={ acosSlbHttp3S 3 } 

		slbHttp3ServerConnTotal OBJECT-TYPE
		SYNTAX  CounterBasedGauge64 
		MAX-ACCESS read-only 
		STATUS current
		DESCRIPTION  "Total HTTP/3 Server Connections" 
		::={ acosSlbHttp3S 4 } 

		slbHttp3ClientConnPeak OBJECT-TYPE
		SYNTAX  CounterBasedGauge64 
		MAX-ACCESS read-only 
		STATUS current
		DESCRIPTION  "Peak HTTP/3 Client Connections" 
		::={ acosSlbHttp3S 5 } 

		slbHttp3ServerConnPeak OBJECT-TYPE
		SYNTAX  CounterBasedGauge64 
		MAX-ACCESS read-only 
		STATUS current
		DESCRIPTION  "Peak HTTP/3 Server Connections" 
		::={ acosSlbHttp3S 6 } 

		slbHttp3ClientRequestStreamsCurr OBJECT-TYPE
		SYNTAX  CounterBasedGauge64 
		MAX-ACCESS read-only 
		STATUS current
		DESCRIPTION  "Current Request Streams on client side" 
		::={ acosSlbHttp3S 7 } 

		slbHttp3ServerRequestStreamsCurr OBJECT-TYPE
		SYNTAX  CounterBasedGauge64 
		MAX-ACCESS read-only 
		STATUS current
		DESCRIPTION  "Current Request Streams on server side" 
		::={ acosSlbHttp3S 8 } 

		slbHttp3ClientRequestStreamsTotal OBJECT-TYPE
		SYNTAX  CounterBasedGauge64 
		MAX-ACCESS read-only 
		STATUS current
		DESCRIPTION  "Total Request Streams on client side" 
		::={ acosSlbHttp3S 9 } 

		slbHttp3ServerRequestStreamsTotal OBJECT-TYPE
		SYNTAX  CounterBasedGauge64 
		MAX-ACCESS read-only 
		STATUS current
		DESCRIPTION  "Total Request Streams on server side" 
		::={ acosSlbHttp3S 10 } 

		slbHttp3ClientPushStreamsCurr OBJECT-TYPE
		SYNTAX  CounterBasedGauge64 
		MAX-ACCESS read-only 
		STATUS current
		DESCRIPTION  "Current Push Streams on client side" 
		::={ acosSlbHttp3S 11 } 

		slbHttp3ServerPushStreamsCurr OBJECT-TYPE
		SYNTAX  CounterBasedGauge64 
		MAX-ACCESS read-only 
		STATUS current
		DESCRIPTION  "Current Push Streams on server side" 
		::={ acosSlbHttp3S 12 } 

		slbHttp3ClientPushStreamsTotal OBJECT-TYPE
		SYNTAX  CounterBasedGauge64 
		MAX-ACCESS read-only 
		STATUS current
		DESCRIPTION  "Total Push Streams on client side" 
		::={ acosSlbHttp3S 13 } 

		slbHttp3ServerPushStreamsTotal OBJECT-TYPE
		SYNTAX  CounterBasedGauge64 
		MAX-ACCESS read-only 
		STATUS current
		DESCRIPTION  "Total Push Streams on server side" 
		::={ acosSlbHttp3S 14 } 

		slbHttp3ClientOtherStreamsCurr OBJECT-TYPE
		SYNTAX  CounterBasedGauge64 
		MAX-ACCESS read-only 
		STATUS current
		DESCRIPTION  "Current Other Streams on client side (control, decoder, encoder)" 
		::={ acosSlbHttp3S 15 } 

		slbHttp3ServerOtherStreamsCurr OBJECT-TYPE
		SYNTAX  CounterBasedGauge64 
		MAX-ACCESS read-only 
		STATUS current
		DESCRIPTION  "urrent Other Streams on server side (control, decoder, encoder)" 
		::={ acosSlbHttp3S 16 } 

		slbHttp3ClientOtherStreamsTotal OBJECT-TYPE
		SYNTAX  CounterBasedGauge64 
		MAX-ACCESS read-only 
		STATUS current
		DESCRIPTION  "Total Other Streams on client side (control, decoder, encoder)" 
		::={ acosSlbHttp3S 17 } 

		slbHttp3ServerOtherStreamsTotal OBJECT-TYPE
		SYNTAX  CounterBasedGauge64 
		MAX-ACCESS read-only 
		STATUS current
		DESCRIPTION  "Total Other Streams on server side (control, decoder, encoder)" 
		::={ acosSlbHttp3S 18 } 

		slbHttpClientFrameTypeHeadersRcvd OBJECT-TYPE
		SYNTAX  CounterBasedGauge64 
		MAX-ACCESS read-only 
		STATUS current
		DESCRIPTION  "HEADERS Frame received on client side" 
		::={ acosSlbHttp3S 19 } 

		slbHttpClientFrameTypeHeadersSent OBJECT-TYPE
		SYNTAX  CounterBasedGauge64 
		MAX-ACCESS read-only 
		STATUS current
		DESCRIPTION  "HEADERS Frame sent on client side" 
		::={ acosSlbHttp3S 20 } 

		slbHttpClientFrameTypeDataRcvd OBJECT-TYPE
		SYNTAX  CounterBasedGauge64 
		MAX-ACCESS read-only 
		STATUS current
		DESCRIPTION  "DATA Frame received on client side" 
		::={ acosSlbHttp3S 21 } 

		slbHttpClientFrameTypeDataSent OBJECT-TYPE
		SYNTAX  CounterBasedGauge64 
		MAX-ACCESS read-only 
		STATUS current
		DESCRIPTION  "DATA Frame sent on client side" 
		::={ acosSlbHttp3S 22 } 

		slbHttpClientFrameTypeCancelPushRcvd OBJECT-TYPE
		SYNTAX  CounterBasedGauge64 
		MAX-ACCESS read-only 
		STATUS current
		DESCRIPTION  "CANCEL PUSH Frame received on client side" 
		::={ acosSlbHttp3S 23 } 

		slbHttpClientFrameTypeCancelPushSent OBJECT-TYPE
		SYNTAX  CounterBasedGauge64 
		MAX-ACCESS read-only 
		STATUS current
		DESCRIPTION  "CANCEL PUSH Frame sent on client side" 
		::={ acosSlbHttp3S 24 } 

		slbHttpClientFrameTypeSettingsRcvd OBJECT-TYPE
		SYNTAX  CounterBasedGauge64 
		MAX-ACCESS read-only 
		STATUS current
		DESCRIPTION  "SETTINGS Frame received on client side" 
		::={ acosSlbHttp3S 25 } 

		slbHttpClientFrameTypeSettingsSent OBJECT-TYPE
		SYNTAX  CounterBasedGauge64 
		MAX-ACCESS read-only 
		STATUS current
		DESCRIPTION  "SETTINGS Frame sent on client side" 
		::={ acosSlbHttp3S 26 } 

		slbHttpClientFrameTypePushPromiseRcvd OBJECT-TYPE
		SYNTAX  CounterBasedGauge64 
		MAX-ACCESS read-only 
		STATUS current
		DESCRIPTION  "PUSH PROMISE Frame received on client side" 
		::={ acosSlbHttp3S 27 } 

		slbHttpClientFrameTypePushPromiseSent OBJECT-TYPE
		SYNTAX  CounterBasedGauge64 
		MAX-ACCESS read-only 
		STATUS current
		DESCRIPTION  "PUSH PROMISE Frame sent on client side" 
		::={ acosSlbHttp3S 28 } 

		slbHttpClientFrameTypeGoawayRcvd OBJECT-TYPE
		SYNTAX  CounterBasedGauge64 
		MAX-ACCESS read-only 
		STATUS current
		DESCRIPTION  "GOAWAY Frame received on client side" 
		::={ acosSlbHttp3S 29 } 

		slbHttpClientFrameTypeGoawaySent OBJECT-TYPE
		SYNTAX  CounterBasedGauge64 
		MAX-ACCESS read-only 
		STATUS current
		DESCRIPTION  "GOAWAY Frame sent on client side" 
		::={ acosSlbHttp3S 30 } 

		slbHttpClientFrameTypeMaxPushIdRcvd OBJECT-TYPE
		SYNTAX  CounterBasedGauge64 
		MAX-ACCESS read-only 
		STATUS current
		DESCRIPTION  "MAX PUSH ID Frame received on client side" 
		::={ acosSlbHttp3S 31 } 

		slbHttpClientFrameTypeMaxPushIdSent OBJECT-TYPE
		SYNTAX  CounterBasedGauge64 
		MAX-ACCESS read-only 
		STATUS current
		DESCRIPTION  "MAX PUSH ID Frame sent on client side" 
		::={ acosSlbHttp3S 32 } 

		slbHttpClientFrameTypeUnknownRcvd OBJECT-TYPE
		SYNTAX  CounterBasedGauge64 
		MAX-ACCESS read-only 
		STATUS current
		DESCRIPTION  "Unknown Frame received on client side" 
		::={ acosSlbHttp3S 33 } 

		clientHeaderFramesToApp OBJECT-TYPE
		SYNTAX  CounterBasedGauge64 
		MAX-ACCESS read-only 
		STATUS current
		DESCRIPTION  "HEADER Frames passed to HTTP layer on client side" 
		::={ acosSlbHttp3S 34 } 

		clientDataFramesToApp OBJECT-TYPE
		SYNTAX  CounterBasedGauge64 
		MAX-ACCESS read-only 
		STATUS current
		DESCRIPTION  "DATA Frames passed to HTTP layer on client side" 
		::={ acosSlbHttp3S 35 } 

		clientHeaderBytesRcvd OBJECT-TYPE
		SYNTAX  CounterBasedGauge64 
		MAX-ACCESS read-only 
		STATUS current
		DESCRIPTION  "Bytes received in HEADER frames on client side" 
		::={ acosSlbHttp3S 36 } 

		clientHeaderBytesSent OBJECT-TYPE
		SYNTAX  CounterBasedGauge64 
		MAX-ACCESS read-only 
		STATUS current
		DESCRIPTION  "Bytes sent in HEADER frames on client side" 
		::={ acosSlbHttp3S 37 } 

		clientDataBytesRcvd OBJECT-TYPE
		SYNTAX  CounterBasedGauge64 
		MAX-ACCESS read-only 
		STATUS current
		DESCRIPTION  "Bytes received in DATA frames on client side" 
		::={ acosSlbHttp3S 38 } 

		clientDataBytesSent OBJECT-TYPE
		SYNTAX  CounterBasedGauge64 
		MAX-ACCESS read-only 
		STATUS current
		DESCRIPTION  "Bytes sent in DATA frames on client side" 
		::={ acosSlbHttp3S 39 } 

		clientOtherFrameBytesRcvd OBJECT-TYPE
		SYNTAX  CounterBasedGauge64 
		MAX-ACCESS read-only 
		STATUS current
		DESCRIPTION  "Bytes received in other frames (SETTINGS, GOAWAY, PUSH_PROMISE etc) on client side" 
		::={ acosSlbHttp3S 40 } 

		clientOtherFrameBytesSent OBJECT-TYPE
		SYNTAX  CounterBasedGauge64 
		MAX-ACCESS read-only 
		STATUS current
		DESCRIPTION  "Bytes sent in other frames (SETTINGS, GOAWAY, PUSH_PROMISE etc) on client side" 
		::={ acosSlbHttp3S 41 } 

		clientHeadingBytesRcvd OBJECT-TYPE
		SYNTAX  CounterBasedGauge64 
		MAX-ACCESS read-only 
		STATUS current
		DESCRIPTION  "Bytes received in HEADERS/DATA frame/stream heading on client side" 
		::={ acosSlbHttp3S 42 } 

		clientHeadingBytesSent OBJECT-TYPE
		SYNTAX  CounterBasedGauge64 
		MAX-ACCESS read-only 
		STATUS current
		DESCRIPTION  "Bytes sent in HEADERS/DATA frame/stream heading on client side" 
		::={ acosSlbHttp3S 43 } 

		clientTotalBytesRcvd OBJECT-TYPE
		SYNTAX  CounterBasedGauge64 
		MAX-ACCESS read-only 
		STATUS current
		DESCRIPTION  "Total Bytes received on client side" 
		::={ acosSlbHttp3S 44 } 

		clientTotalBytesSent OBJECT-TYPE
		SYNTAX  CounterBasedGauge64 
		MAX-ACCESS read-only 
		STATUS current
		DESCRIPTION  "Total Bytes sent on client side" 
		::={ acosSlbHttp3S 45 } 

		slbHttpServerFrameTypeHeadersRcvd OBJECT-TYPE
		SYNTAX  CounterBasedGauge64 
		MAX-ACCESS read-only 
		STATUS current
		DESCRIPTION  "HEADERS Frame received on server side" 
		::={ acosSlbHttp3S 46 } 

		slbHttpServerFrameTypeHeadersSent OBJECT-TYPE
		SYNTAX  CounterBasedGauge64 
		MAX-ACCESS read-only 
		STATUS current
		DESCRIPTION  "HEADERS Frame sent on server side" 
		::={ acosSlbHttp3S 47 } 

		slbHttpServerFrameTypeDataRcvd OBJECT-TYPE
		SYNTAX  CounterBasedGauge64 
		MAX-ACCESS read-only 
		STATUS current
		DESCRIPTION  "DATA Frame received on server side" 
		::={ acosSlbHttp3S 48 } 

		slbHttpServerFrameTypeDataSent OBJECT-TYPE
		SYNTAX  CounterBasedGauge64 
		MAX-ACCESS read-only 
		STATUS current
		DESCRIPTION  "DATA Frame sent on server side" 
		::={ acosSlbHttp3S 49 } 

		slbHttpServerFrameTypeCancelPushRcvd OBJECT-TYPE
		SYNTAX  CounterBasedGauge64 
		MAX-ACCESS read-only 
		STATUS current
		DESCRIPTION  "CANCEL PUSH Frame received on server side" 
		::={ acosSlbHttp3S 50 } 

		slbHttpServerFrameTypeCancelPushSent OBJECT-TYPE
		SYNTAX  CounterBasedGauge64 
		MAX-ACCESS read-only 
		STATUS current
		DESCRIPTION  "CANCEL PUSH Frame sent on server side" 
		::={ acosSlbHttp3S 51 } 

		slbHttpServerFrameTypeSettingsRcvd OBJECT-TYPE
		SYNTAX  CounterBasedGauge64 
		MAX-ACCESS read-only 
		STATUS current
		DESCRIPTION  "SETTINGS Frame received on server side" 
		::={ acosSlbHttp3S 52 } 

		slbHttpServerFrameTypeSettingsSent OBJECT-TYPE
		SYNTAX  CounterBasedGauge64 
		MAX-ACCESS read-only 
		STATUS current
		DESCRIPTION  "SETTINGS Frame sent on server side" 
		::={ acosSlbHttp3S 53 } 

		slbHttpServerFrameTypePushPromiseRcvd OBJECT-TYPE
		SYNTAX  CounterBasedGauge64 
		MAX-ACCESS read-only 
		STATUS current
		DESCRIPTION  "PUSH PROMISE Frame received on server side" 
		::={ acosSlbHttp3S 54 } 

		slbHttpServerFrameTypePushPromiseSent OBJECT-TYPE
		SYNTAX  CounterBasedGauge64 
		MAX-ACCESS read-only 
		STATUS current
		DESCRIPTION  "PUSH PROMISE Frame sent on server side" 
		::={ acosSlbHttp3S 55 } 

		slbHttpServerFrameTypeGoawayRcvd OBJECT-TYPE
		SYNTAX  CounterBasedGauge64 
		MAX-ACCESS read-only 
		STATUS current
		DESCRIPTION  "GOAWAY Frame received on server side" 
		::={ acosSlbHttp3S 56 } 

		slbHttpServerFrameTypeGoawaySent OBJECT-TYPE
		SYNTAX  CounterBasedGauge64 
		MAX-ACCESS read-only 
		STATUS current
		DESCRIPTION  "GOAWAY Frame sent on server side" 
		::={ acosSlbHttp3S 57 } 

		slbHttpServerFrameTypeMaxPushIdRcvd OBJECT-TYPE
		SYNTAX  CounterBasedGauge64 
		MAX-ACCESS read-only 
		STATUS current
		DESCRIPTION  "MAX PUSH ID Frame received on server side" 
		::={ acosSlbHttp3S 58 } 

		slbHttpServerFrameTypeMaxPushIdSent OBJECT-TYPE
		SYNTAX  CounterBasedGauge64 
		MAX-ACCESS read-only 
		STATUS current
		DESCRIPTION  "MAX PUSH ID Frame sent on server side" 
		::={ acosSlbHttp3S 59 } 

		slbHttpServerFrameTypeUnknownRcvd OBJECT-TYPE
		SYNTAX  CounterBasedGauge64 
		MAX-ACCESS read-only 
		STATUS current
		DESCRIPTION  "Unknown Frame received on server side" 
		::={ acosSlbHttp3S 60 } 

		serverHeaderFramesToApp OBJECT-TYPE
		SYNTAX  CounterBasedGauge64 
		MAX-ACCESS read-only 
		STATUS current
		DESCRIPTION  "HEADER Frames passed to HTTP layer on server side" 
		::={ acosSlbHttp3S 61 } 

		serverDataFramesToApp OBJECT-TYPE
		SYNTAX  CounterBasedGauge64 
		MAX-ACCESS read-only 
		STATUS current
		DESCRIPTION  "DATA Frames passed to HTTP layer on server side" 
		::={ acosSlbHttp3S 62 } 

		serverHeaderBytesRcvd OBJECT-TYPE
		SYNTAX  CounterBasedGauge64 
		MAX-ACCESS read-only 
		STATUS current
		DESCRIPTION  "Bytes received in HEADER frames on server side" 
		::={ acosSlbHttp3S 63 } 

		serverHeaderBytesSent OBJECT-TYPE
		SYNTAX  CounterBasedGauge64 
		MAX-ACCESS read-only 
		STATUS current
		DESCRIPTION  "Bytes sent in HEADER frames on server side" 
		::={ acosSlbHttp3S 64 } 

		serverDataBytesRcvd OBJECT-TYPE
		SYNTAX  CounterBasedGauge64 
		MAX-ACCESS read-only 
		STATUS current
		DESCRIPTION  "Bytes received in DATA frames on server side" 
		::={ acosSlbHttp3S 65 } 

		serverDataBytesSent OBJECT-TYPE
		SYNTAX  CounterBasedGauge64 
		MAX-ACCESS read-only 
		STATUS current
		DESCRIPTION  "Bytes sent in DATA frames on server side" 
		::={ acosSlbHttp3S 66 } 

		serverOtherFrameBytesRcvd OBJECT-TYPE
		SYNTAX  CounterBasedGauge64 
		MAX-ACCESS read-only 
		STATUS current
		DESCRIPTION  "Bytes received in other frames (SETTINGS, GOAWAY, PUSH_PROMISE etc) on server side" 
		::={ acosSlbHttp3S 67 } 

		serverOtherFrameBytesSent OBJECT-TYPE
		SYNTAX  CounterBasedGauge64 
		MAX-ACCESS read-only 
		STATUS current
		DESCRIPTION  "Bytes sent in other frames (SETTINGS, GOAWAY, PUSH_PROMISE etc) on server side" 
		::={ acosSlbHttp3S 68 } 

		serverHeadingBytesRcvd OBJECT-TYPE
		SYNTAX  CounterBasedGauge64 
		MAX-ACCESS read-only 
		STATUS current
		DESCRIPTION  "Bytes received in HEADERS/DATA frame/stream heading on server side" 
		::={ acosSlbHttp3S 69 } 

		serverHeadingBytesSent OBJECT-TYPE
		SYNTAX  CounterBasedGauge64 
		MAX-ACCESS read-only 
		STATUS current
		DESCRIPTION  "Bytes sent in HEADERS/DATA frame/stream heading on server side" 
		::={ acosSlbHttp3S 70 } 

		serverTotalBytesRcvd OBJECT-TYPE
		SYNTAX  CounterBasedGauge64 
		MAX-ACCESS read-only 
		STATUS current
		DESCRIPTION  "Total Bytes received on server side" 
		::={ acosSlbHttp3S 71 } 

		serverTotalBytesSent OBJECT-TYPE
		SYNTAX  CounterBasedGauge64 
		MAX-ACCESS read-only 
		STATUS current
		DESCRIPTION  "Total Bytes sent on server side" 
		::={ acosSlbHttp3S 72 } 

		slbHttp3InvalidArgument OBJECT-TYPE
		SYNTAX  CounterBasedGauge64 
		MAX-ACCESS read-only 
		STATUS current
		DESCRIPTION  "Invalid Argument" 
		::={ acosSlbHttp3S 73 } 

		slbHttp3InvalidState OBJECT-TYPE
		SYNTAX  CounterBasedGauge64 
		MAX-ACCESS read-only 
		STATUS current
		DESCRIPTION  "Invalid State" 
		::={ acosSlbHttp3S 74 } 

		slbHttp3Wouldblock OBJECT-TYPE
		SYNTAX  CounterBasedGauge64 
		MAX-ACCESS read-only 
		STATUS current
		DESCRIPTION  "Wouldblock" 
		::={ acosSlbHttp3S 75 } 

		slbHttp3StreamInUse OBJECT-TYPE
		SYNTAX  CounterBasedGauge64 
		MAX-ACCESS read-only 
		STATUS current
		DESCRIPTION  "Stream In Use" 
		::={ acosSlbHttp3S 76 } 

		slbHttp3PushIdBlocked OBJECT-TYPE
		SYNTAX  CounterBasedGauge64 
		MAX-ACCESS read-only 
		STATUS current
		DESCRIPTION  "Push Id Blocked" 
		::={ acosSlbHttp3S 77 } 

		slbHttp3MalformedHttpHeader OBJECT-TYPE
		SYNTAX  CounterBasedGauge64 
		MAX-ACCESS read-only 
		STATUS current
		DESCRIPTION  "Malformed Http Header" 
		::={ acosSlbHttp3S 78 } 

		slbHttp3RemoveHttpHeader OBJECT-TYPE
		SYNTAX  CounterBasedGauge64 
		MAX-ACCESS read-only 
		STATUS current
		DESCRIPTION  "Remove Http Header" 
		::={ acosSlbHttp3S 79 } 

		slbHttp3MalformedHttpMessaging OBJECT-TYPE
		SYNTAX  CounterBasedGauge64 
		MAX-ACCESS read-only 
		STATUS current
		DESCRIPTION  "Malformed Http Messaging" 
		::={ acosSlbHttp3S 80 } 

		slbHttp3TooLate OBJECT-TYPE
		SYNTAX  CounterBasedGauge64 
		MAX-ACCESS read-only 
		STATUS current
		DESCRIPTION  "Too Late" 
		::={ acosSlbHttp3S 81 } 

		slbHttp3QpackFatal OBJECT-TYPE
		SYNTAX  CounterBasedGauge64 
		MAX-ACCESS read-only 
		STATUS current
		DESCRIPTION  "Qpack Fatal" 
		::={ acosSlbHttp3S 82 } 

		slbHttp3QpackHeaderTooLarge OBJECT-TYPE
		SYNTAX  CounterBasedGauge64 
		MAX-ACCESS read-only 
		STATUS current
		DESCRIPTION  "Qpack Header Too Large" 
		::={ acosSlbHttp3S 83 } 

		slbHttp3IgnoreStream OBJECT-TYPE
		SYNTAX  CounterBasedGauge64 
		MAX-ACCESS read-only 
		STATUS current
		DESCRIPTION  "Ignore Stream" 
		::={ acosSlbHttp3S 84 } 

		slbHttp3StreamNotFound OBJECT-TYPE
		SYNTAX  CounterBasedGauge64 
		MAX-ACCESS read-only 
		STATUS current
		DESCRIPTION  "Stream Not Found" 
		::={ acosSlbHttp3S 85 } 

		slbHttp3IgnorePushPromise OBJECT-TYPE
		SYNTAX  CounterBasedGauge64 
		MAX-ACCESS read-only 
		STATUS current
		DESCRIPTION  "Ignore Push Promise" 
		::={ acosSlbHttp3S 86 } 

		slbHttp3QpackDecompressionFailed OBJECT-TYPE
		SYNTAX  CounterBasedGauge64 
		MAX-ACCESS read-only 
		STATUS current
		DESCRIPTION  "Qpack Decompression Failed" 
		::={ acosSlbHttp3S 87 } 

		slbHttp3QpackEncoderStreamError OBJECT-TYPE
		SYNTAX  CounterBasedGauge64 
		MAX-ACCESS read-only 
		STATUS current
		DESCRIPTION  "Qpack Encoder Stream Error" 
		::={ acosSlbHttp3S 88 } 

		slbHttp3QpackDecoderStreamError OBJECT-TYPE
		SYNTAX  CounterBasedGauge64 
		MAX-ACCESS read-only 
		STATUS current
		DESCRIPTION  "Qpack Decoder Stream Error" 
		::={ acosSlbHttp3S 89 } 

		slbHttp3H3FrameUnexpected OBJECT-TYPE
		SYNTAX  CounterBasedGauge64 
		MAX-ACCESS read-only 
		STATUS current
		DESCRIPTION  "H3 Frame Unexpected" 
		::={ acosSlbHttp3S 90 } 

		slbHttp3H3FrameError OBJECT-TYPE
		SYNTAX  CounterBasedGauge64 
		MAX-ACCESS read-only 
		STATUS current
		DESCRIPTION  "H3 Frame Error" 
		::={ acosSlbHttp3S 91 } 

		slbHttp3H3MissingSettings OBJECT-TYPE
		SYNTAX  CounterBasedGauge64 
		MAX-ACCESS read-only 
		STATUS current
		DESCRIPTION  "H3 Missing Settings" 
		::={ acosSlbHttp3S 92 } 

		slbHttp3H3InternalError OBJECT-TYPE
		SYNTAX  CounterBasedGauge64 
		MAX-ACCESS read-only 
		STATUS current
		DESCRIPTION  "H3 Internal Error" 
		::={ acosSlbHttp3S 93 } 

		slbHttp3H3ClosedCriticalStream OBJECT-TYPE
		SYNTAX  CounterBasedGauge64 
		MAX-ACCESS read-only 
		STATUS current
		DESCRIPTION  "H3 Closed Critical Stream" 
		::={ acosSlbHttp3S 94 } 

		slbHttp3H3GeneralProtocolError OBJECT-TYPE
		SYNTAX  CounterBasedGauge64 
		MAX-ACCESS read-only 
		STATUS current
		DESCRIPTION  "H3 General Protocol Error" 
		::={ acosSlbHttp3S 95 } 

		slbHttp3H3IdError OBJECT-TYPE
		SYNTAX  CounterBasedGauge64 
		MAX-ACCESS read-only 
		STATUS current
		DESCRIPTION  "H3 Id Error" 
		::={ acosSlbHttp3S 96 } 

		slbHttp3H3SettingsError OBJECT-TYPE
		SYNTAX  CounterBasedGauge64 
		MAX-ACCESS read-only 
		STATUS current
		DESCRIPTION  "H3 Settings Error" 
		::={ acosSlbHttp3S 97 } 

		slbHttp3H3StreamCreationError OBJECT-TYPE
		SYNTAX  CounterBasedGauge64 
		MAX-ACCESS read-only 
		STATUS current
		DESCRIPTION  "H3 Stream Creation Error" 
		::={ acosSlbHttp3S 98 } 

		slbHttp3Fatal OBJECT-TYPE
		SYNTAX  CounterBasedGauge64 
		MAX-ACCESS read-only 
		STATUS current
		DESCRIPTION  "Fatal Error" 
		::={ acosSlbHttp3S 99 } 

		connAllocError OBJECT-TYPE
		SYNTAX  CounterBasedGauge64 
		MAX-ACCESS read-only 
		STATUS current
		DESCRIPTION  "HTTP/3 Connection Allocation Error" 
		::={ acosSlbHttp3S 100 } 

		allocFailTotal OBJECT-TYPE
		SYNTAX  CounterBasedGauge64 
		MAX-ACCESS read-only 
		STATUS current
		DESCRIPTION  "Memory Allocation Failures" 
		::={ acosSlbHttp3S 101 } 

		slbHttp3Rejected OBJECT-TYPE
		SYNTAX  CounterBasedGauge64 
		MAX-ACCESS read-only 
		STATUS current
		DESCRIPTION  "HTTP3 Rejected" 
		::={ acosSlbHttp3S 102 } 

acosSlbL7session                    OBJECT IDENTIFIER ::= { acosSlb 64 }
acosSlbL7sessionS                   OBJECT IDENTIFIER ::= { acosSlbL7session 1 }

		startServerConnSucc OBJECT-TYPE
		SYNTAX  CounterBasedGauge64 
		MAX-ACCESS read-only 
		STATUS current
		DESCRIPTION  "Start Server Conn Success" 
		::={ acosSlbL7sessionS 1 } 

		connNotExist OBJECT-TYPE
		SYNTAX  CounterBasedGauge64 
		MAX-ACCESS read-only 
		STATUS current
		DESCRIPTION  "Conn does not exist" 
		::={ acosSlbL7sessionS 2 } 

		dataEvent OBJECT-TYPE
		SYNTAX  CounterBasedGauge64 
		MAX-ACCESS read-only 
		STATUS current
		DESCRIPTION  "Data event from TCP" 
		::={ acosSlbL7sessionS 3 } 

		clientFin OBJECT-TYPE
		SYNTAX  CounterBasedGauge64 
		MAX-ACCESS read-only 
		STATUS current
		DESCRIPTION  "FIN from client" 
		::={ acosSlbL7sessionS 4 } 

		serverFin OBJECT-TYPE
		SYNTAX  CounterBasedGauge64 
		MAX-ACCESS read-only 
		STATUS current
		DESCRIPTION  "FIN from server" 
		::={ acosSlbL7sessionS 5 } 

		wbufEvent OBJECT-TYPE
		SYNTAX  CounterBasedGauge64 
		MAX-ACCESS read-only 
		STATUS current
		DESCRIPTION  "Wbuf event from TCP" 
		::={ acosSlbL7sessionS 6 } 

		wbufCbFailed OBJECT-TYPE
		SYNTAX  CounterBasedGauge64 
		MAX-ACCESS read-only 
		STATUS current
		DESCRIPTION  "Wbuf event callback failed" 
		::={ acosSlbL7sessionS 7 } 

		errEvent OBJECT-TYPE
		SYNTAX  CounterBasedGauge64 
		MAX-ACCESS read-only 
		STATUS current
		DESCRIPTION  "Err event from TCP" 
		::={ acosSlbL7sessionS 8 } 

		errCbFailed OBJECT-TYPE
		SYNTAX  CounterBasedGauge64 
		MAX-ACCESS read-only 
		STATUS current
		DESCRIPTION  "Err event callback failed" 
		::={ acosSlbL7sessionS 9 } 

		serverConnFailed OBJECT-TYPE
		SYNTAX  CounterBasedGauge64 
		MAX-ACCESS read-only 
		STATUS current
		DESCRIPTION  "Server connection failed" 
		::={ acosSlbL7sessionS 10 } 

		clientRst OBJECT-TYPE
		SYNTAX  CounterBasedGauge64 
		MAX-ACCESS read-only 
		STATUS current
		DESCRIPTION  "RST from client" 
		::={ acosSlbL7sessionS 11 } 

		serverRst OBJECT-TYPE
		SYNTAX  CounterBasedGauge64 
		MAX-ACCESS read-only 
		STATUS current
		DESCRIPTION  "RST from server" 
		::={ acosSlbL7sessionS 12 } 

		clientRstReq OBJECT-TYPE
		SYNTAX  CounterBasedGauge64 
		MAX-ACCESS read-only 
		STATUS current
		DESCRIPTION  "RST from client - request" 
		::={ acosSlbL7sessionS 13 } 

		clientRstConnecting OBJECT-TYPE
		SYNTAX  CounterBasedGauge64 
		MAX-ACCESS read-only 
		STATUS current
		DESCRIPTION  "RST from client - connecting" 
		::={ acosSlbL7sessionS 14 } 

		clientRstConnected OBJECT-TYPE
		SYNTAX  CounterBasedGauge64 
		MAX-ACCESS read-only 
		STATUS current
		DESCRIPTION  "RST from client - connected" 
		::={ acosSlbL7sessionS 15 } 

		clientRstRsp OBJECT-TYPE
		SYNTAX  CounterBasedGauge64 
		MAX-ACCESS read-only 
		STATUS current
		DESCRIPTION  "RST from client - response" 
		::={ acosSlbL7sessionS 16 } 

		serverRstReq OBJECT-TYPE
		SYNTAX  CounterBasedGauge64 
		MAX-ACCESS read-only 
		STATUS current
		DESCRIPTION  "RST from server - request" 
		::={ acosSlbL7sessionS 17 } 

		serverRstConnecting OBJECT-TYPE
		SYNTAX  CounterBasedGauge64 
		MAX-ACCESS read-only 
		STATUS current
		DESCRIPTION  "RST from server - connecting" 
		::={ acosSlbL7sessionS 18 } 

		serverRstConnected OBJECT-TYPE
		SYNTAX  CounterBasedGauge64 
		MAX-ACCESS read-only 
		STATUS current
		DESCRIPTION  "RST from server - connected" 
		::={ acosSlbL7sessionS 19 } 

		serverRstRsp OBJECT-TYPE
		SYNTAX  CounterBasedGauge64 
		MAX-ACCESS read-only 
		STATUS current
		DESCRIPTION  "RST from server - response" 
		::={ acosSlbL7sessionS 20 } 

		proxyV1Connection OBJECT-TYPE
		SYNTAX  CounterBasedGauge64 
		MAX-ACCESS read-only 
		STATUS current
		DESCRIPTION  "counter for Proxy v1 connection" 
		::={ acosSlbL7sessionS 21 } 

		proxyV2Connection OBJECT-TYPE
		SYNTAX  CounterBasedGauge64 
		MAX-ACCESS read-only 
		STATUS current
		DESCRIPTION  "counter for Proxy v2 connection" 
		::={ acosSlbL7sessionS 22 } 

		currProxy OBJECT-TYPE
		SYNTAX  CounterBasedGauge64 
		MAX-ACCESS read-only 
		STATUS current
		DESCRIPTION  "Curr proxy conn" 
		::={ acosSlbL7sessionS 23 } 

		currProxyClient OBJECT-TYPE
		SYNTAX  CounterBasedGauge64 
		MAX-ACCESS read-only 
		STATUS current
		DESCRIPTION  "Curr proxy conn - client" 
		::={ acosSlbL7sessionS 24 } 

		currProxyServer OBJECT-TYPE
		SYNTAX  CounterBasedGauge64 
		MAX-ACCESS read-only 
		STATUS current
		DESCRIPTION  "Curr proxy conn - server" 
		::={ acosSlbL7sessionS 25 } 

		currProxyEs OBJECT-TYPE
		SYNTAX  CounterBasedGauge64 
		MAX-ACCESS read-only 
		STATUS current
		DESCRIPTION  "Curr proxy conn - ES" 
		::={ acosSlbL7sessionS 26 } 

		totalProxy OBJECT-TYPE
		SYNTAX  CounterBasedGauge64 
		MAX-ACCESS read-only 
		STATUS current
		DESCRIPTION  "Total proxy conn" 
		::={ acosSlbL7sessionS 27 } 

		totalProxyClient OBJECT-TYPE
		SYNTAX  CounterBasedGauge64 
		MAX-ACCESS read-only 
		STATUS current
		DESCRIPTION  "Total proxy conn - client" 
		::={ acosSlbL7sessionS 28 } 

		totalProxyServer OBJECT-TYPE
		SYNTAX  CounterBasedGauge64 
		MAX-ACCESS read-only 
		STATUS current
		DESCRIPTION  "Total proxy conn - server" 
		::={ acosSlbL7sessionS 29 } 

		totalProxyEs OBJECT-TYPE
		SYNTAX  CounterBasedGauge64 
		MAX-ACCESS read-only 
		STATUS current
		DESCRIPTION  "Total proxy conn - ES" 
		::={ acosSlbL7sessionS 30 } 

		serverSelectFail OBJECT-TYPE
		SYNTAX  CounterBasedGauge64 
		MAX-ACCESS read-only 
		STATUS current
		DESCRIPTION  "Server selection fail" 
		::={ acosSlbL7sessionS 31 } 

		estEvent OBJECT-TYPE
		SYNTAX  CounterBasedGauge64 
		MAX-ACCESS read-only 
		STATUS current
		DESCRIPTION  "Est event from TCP" 
		::={ acosSlbL7sessionS 32 } 

		estCbFailed OBJECT-TYPE
		SYNTAX  CounterBasedGauge64 
		MAX-ACCESS read-only 
		STATUS current
		DESCRIPTION  "Est event callback fail" 
		::={ acosSlbL7sessionS 33 } 

		dataCbFailed OBJECT-TYPE
		SYNTAX  CounterBasedGauge64 
		MAX-ACCESS read-only 
		STATUS current
		DESCRIPTION  "Data event callback fail" 
		::={ acosSlbL7sessionS 34 } 

		hpsFwdreqFail OBJECT-TYPE
		SYNTAX  CounterBasedGauge64 
		MAX-ACCESS read-only 
		STATUS current
		DESCRIPTION  "Fwd req fail" 
		::={ acosSlbL7sessionS 35 } 

		hpsFwdreqFailBuff OBJECT-TYPE
		SYNTAX  CounterBasedGauge64 
		MAX-ACCESS read-only 
		STATUS current
		DESCRIPTION  "Fwd req fail - buff" 
		::={ acosSlbL7sessionS 36 } 

		hpsFwdreqFailRport OBJECT-TYPE
		SYNTAX  CounterBasedGauge64 
		MAX-ACCESS read-only 
		STATUS current
		DESCRIPTION  "Fwd req fail - rport" 
		::={ acosSlbL7sessionS 37 } 

		hpsFwdreqFailRoute OBJECT-TYPE
		SYNTAX  CounterBasedGauge64 
		MAX-ACCESS read-only 
		STATUS current
		DESCRIPTION  "Fwd req fail - route" 
		::={ acosSlbL7sessionS 38 } 

		hpsFwdreqFailPersist OBJECT-TYPE
		SYNTAX  CounterBasedGauge64 
		MAX-ACCESS read-only 
		STATUS current
		DESCRIPTION  "Fwd req fail - persist" 
		::={ acosSlbL7sessionS 39 } 

		hpsFwdreqFailServer OBJECT-TYPE
		SYNTAX  CounterBasedGauge64 
		MAX-ACCESS read-only 
		STATUS current
		DESCRIPTION  "Fwd req fail - server" 
		::={ acosSlbL7sessionS 40 } 

		hpsFwdreqFailTuple OBJECT-TYPE
		SYNTAX  CounterBasedGauge64 
		MAX-ACCESS read-only 
		STATUS current
		DESCRIPTION  "Fwd req fail - tuple" 
		::={ acosSlbL7sessionS 41 } 

		udpDataEvent OBJECT-TYPE
		SYNTAX  CounterBasedGauge64 
		MAX-ACCESS read-only 
		STATUS current
		DESCRIPTION  "Data event from UDP" 
		::={ acosSlbL7sessionS 42 } 

		transactionCleaned OBJECT-TYPE
		SYNTAX  CounterBasedGauge64 
		MAX-ACCESS read-only 
		STATUS current
		DESCRIPTION  "Transaction cleaned - tuple" 
		::={ acosSlbL7sessionS 43 } 

		oldServerCleaned OBJECT-TYPE
		SYNTAX  CounterBasedGauge64 
		MAX-ACCESS read-only 
		STATUS current
		DESCRIPTION  "Old server cleaned - tuple" 
		::={ acosSlbL7sessionS 44 } 

		serverNotCleaned OBJECT-TYPE
		SYNTAX  CounterBasedGauge64 
		MAX-ACCESS read-only 
		STATUS current
		DESCRIPTION  "Server not cleaned - tuple" 
		::={ acosSlbL7sessionS 45 } 

		clientNotCleaned OBJECT-TYPE
		SYNTAX  CounterBasedGauge64 
		MAX-ACCESS read-only 
		STATUS current
		DESCRIPTION  "Client not cleaned - tuple" 
		::={ acosSlbL7sessionS 46 } 

		invalidServer OBJECT-TYPE
		SYNTAX  CounterBasedGauge64 
		MAX-ACCESS read-only 
		STATUS current
		DESCRIPTION  "Invalid server - tuple" 
		::={ acosSlbL7sessionS 47 } 

acosSlbSmpp                         OBJECT IDENTIFIER ::= { acosSlb 29 }
acosSlbSmppS                        OBJECT IDENTIFIER ::= { acosSlbSmpp 1 }

		msgProxyCurrent OBJECT-TYPE
		SYNTAX  CounterBasedGauge64 
		MAX-ACCESS read-only 
		STATUS current
		DESCRIPTION  "Curr SMPP Proxy" 
		::={ acosSlbSmppS 1 } 

		msgProxyTotal OBJECT-TYPE
		SYNTAX  CounterBasedGauge64 
		MAX-ACCESS read-only 
		STATUS current
		DESCRIPTION  "Total SMPP Proxy" 
		::={ acosSlbSmppS 2 } 

		msgProxyMemAllocd OBJECT-TYPE
		SYNTAX  CounterBasedGauge64 
		MAX-ACCESS read-only 
		STATUS current
		DESCRIPTION  "" 
		::={ acosSlbSmppS 3 } 

		msgProxyMemCached OBJECT-TYPE
		SYNTAX  CounterBasedGauge64 
		MAX-ACCESS read-only 
		STATUS current
		DESCRIPTION  "" 
		::={ acosSlbSmppS 4 } 

		msgProxyMemFreed OBJECT-TYPE
		SYNTAX  CounterBasedGauge64 
		MAX-ACCESS read-only 
		STATUS current
		DESCRIPTION  "" 
		::={ acosSlbSmppS 5 } 

		msgProxyClientRecv OBJECT-TYPE
		SYNTAX  CounterBasedGauge64 
		MAX-ACCESS read-only 
		STATUS current
		DESCRIPTION  "Client message rcvd" 
		::={ acosSlbSmppS 6 } 

		msgProxyClientSendSuccess OBJECT-TYPE
		SYNTAX  CounterBasedGauge64 
		MAX-ACCESS read-only 
		STATUS current
		DESCRIPTION  "Sent to server" 
		::={ acosSlbSmppS 7 } 

		msgProxyClientIncomplete OBJECT-TYPE
		SYNTAX  CounterBasedGauge64 
		MAX-ACCESS read-only 
		STATUS current
		DESCRIPTION  "Incomplete" 
		::={ acosSlbSmppS 8 } 

		msgProxyClientDrop OBJECT-TYPE
		SYNTAX  CounterBasedGauge64 
		MAX-ACCESS read-only 
		STATUS current
		DESCRIPTION  "AX responds directly" 
		::={ acosSlbSmppS 9 } 

		msgProxyClientConnection OBJECT-TYPE
		SYNTAX  CounterBasedGauge64 
		MAX-ACCESS read-only 
		STATUS current
		DESCRIPTION  "Connecting server" 
		::={ acosSlbSmppS 10 } 

		msgProxyClientFail OBJECT-TYPE
		SYNTAX  CounterBasedGauge64 
		MAX-ACCESS read-only 
		STATUS current
		DESCRIPTION  "Number of SMPP messages received from client but failed to forward to server" 
		::={ acosSlbSmppS 11 } 

		msgProxyClientFailParse OBJECT-TYPE
		SYNTAX  CounterBasedGauge64 
		MAX-ACCESS read-only 
		STATUS current
		DESCRIPTION  "" 
		::={ acosSlbSmppS 12 } 

		msgProxyClientFailProcess OBJECT-TYPE
		SYNTAX  CounterBasedGauge64 
		MAX-ACCESS read-only 
		STATUS current
		DESCRIPTION  "" 
		::={ acosSlbSmppS 13 } 

		msgProxyClientFailSnat OBJECT-TYPE
		SYNTAX  CounterBasedGauge64 
		MAX-ACCESS read-only 
		STATUS current
		DESCRIPTION  "" 
		::={ acosSlbSmppS 14 } 

		msgProxyClientExceedTmpBuff OBJECT-TYPE
		SYNTAX  CounterBasedGauge64 
		MAX-ACCESS read-only 
		STATUS current
		DESCRIPTION  "" 
		::={ acosSlbSmppS 15 } 

		msgProxyClientFailSendPkt OBJECT-TYPE
		SYNTAX  CounterBasedGauge64 
		MAX-ACCESS read-only 
		STATUS current
		DESCRIPTION  "" 
		::={ acosSlbSmppS 16 } 

		msgProxyClientFailStartServerConn OBJECT-TYPE
		SYNTAX  CounterBasedGauge64 
		MAX-ACCESS read-only 
		STATUS current
		DESCRIPTION  "" 
		::={ acosSlbSmppS 17 } 

		msgProxyServerRecv OBJECT-TYPE
		SYNTAX  CounterBasedGauge64 
		MAX-ACCESS read-only 
		STATUS current
		DESCRIPTION  "Server message rcvd" 
		::={ acosSlbSmppS 18 } 

		msgProxyServerSendSuccess OBJECT-TYPE
		SYNTAX  CounterBasedGauge64 
		MAX-ACCESS read-only 
		STATUS current
		DESCRIPTION  "Sent to client" 
		::={ acosSlbSmppS 19 } 

		msgProxyServerIncomplete OBJECT-TYPE
		SYNTAX  CounterBasedGauge64 
		MAX-ACCESS read-only 
		STATUS current
		DESCRIPTION  "Incomplete" 
		::={ acosSlbSmppS 20 } 

		msgProxyServerDrop OBJECT-TYPE
		SYNTAX  CounterBasedGauge64 
		MAX-ACCESS read-only 
		STATUS current
		DESCRIPTION  "Number of the packet AX drop" 
		::={ acosSlbSmppS 21 } 

		msgProxyServerFail OBJECT-TYPE
		SYNTAX  CounterBasedGauge64 
		MAX-ACCESS read-only 
		STATUS current
		DESCRIPTION  "Number of SMPP messages received from server but failed to forward to client" 
		::={ acosSlbSmppS 22 } 

		msgProxyServerFailParse OBJECT-TYPE
		SYNTAX  CounterBasedGauge64 
		MAX-ACCESS read-only 
		STATUS current
		DESCRIPTION  "" 
		::={ acosSlbSmppS 23 } 

		msgProxyServerFailProcess OBJECT-TYPE
		SYNTAX  CounterBasedGauge64 
		MAX-ACCESS read-only 
		STATUS current
		DESCRIPTION  "" 
		::={ acosSlbSmppS 24 } 

		msgProxyServerFailSelecConnt OBJECT-TYPE
		SYNTAX  CounterBasedGauge64 
		MAX-ACCESS read-only 
		STATUS current
		DESCRIPTION  "" 
		::={ acosSlbSmppS 25 } 

		msgProxyServerFailSnat OBJECT-TYPE
		SYNTAX  CounterBasedGauge64 
		MAX-ACCESS read-only 
		STATUS current
		DESCRIPTION  "" 
		::={ acosSlbSmppS 26 } 

		msgProxyServerExceedTmpBuff OBJECT-TYPE
		SYNTAX  CounterBasedGauge64 
		MAX-ACCESS read-only 
		STATUS current
		DESCRIPTION  "" 
		::={ acosSlbSmppS 27 } 

		msgProxyServerFailSendPkt OBJECT-TYPE
		SYNTAX  CounterBasedGauge64 
		MAX-ACCESS read-only 
		STATUS current
		DESCRIPTION  "" 
		::={ acosSlbSmppS 28 } 

		msgProxyCreateServerConn OBJECT-TYPE
		SYNTAX  CounterBasedGauge64 
		MAX-ACCESS read-only 
		STATUS current
		DESCRIPTION  "Server conn created" 
		::={ acosSlbSmppS 29 } 

		msgProxyStartServerConn OBJECT-TYPE
		SYNTAX  CounterBasedGauge64 
		MAX-ACCESS read-only 
		STATUS current
		DESCRIPTION  "Number of server connection created successfully" 
		::={ acosSlbSmppS 30 } 

		msgProxyFailStartServerConn OBJECT-TYPE
		SYNTAX  CounterBasedGauge64 
		MAX-ACCESS read-only 
		STATUS current
		DESCRIPTION  "Number of server connection created failed" 
		::={ acosSlbSmppS 31 } 

		msgProxyServerConnFailSnat OBJECT-TYPE
		SYNTAX  CounterBasedGauge64 
		MAX-ACCESS read-only 
		STATUS current
		DESCRIPTION  "" 
		::={ acosSlbSmppS 32 } 

		msgProxyFailConstructServerConn OBJECT-TYPE
		SYNTAX  CounterBasedGauge64 
		MAX-ACCESS read-only 
		STATUS current
		DESCRIPTION  "" 
		::={ acosSlbSmppS 33 } 

		msgProxyFailReservePconn OBJECT-TYPE
		SYNTAX  CounterBasedGauge64 
		MAX-ACCESS read-only 
		STATUS current
		DESCRIPTION  "" 
		::={ acosSlbSmppS 34 } 

		msgProxyStartServerConnFailed OBJECT-TYPE
		SYNTAX  CounterBasedGauge64 
		MAX-ACCESS read-only 
		STATUS current
		DESCRIPTION  "" 
		::={ acosSlbSmppS 35 } 

		msgProxyServerConnAlreadyExists OBJECT-TYPE
		SYNTAX  CounterBasedGauge64 
		MAX-ACCESS read-only 
		STATUS current
		DESCRIPTION  "" 
		::={ acosSlbSmppS 36 } 

		msgProxyFailInsertServerConn OBJECT-TYPE
		SYNTAX  CounterBasedGauge64 
		MAX-ACCESS read-only 
		STATUS current
		DESCRIPTION  "" 
		::={ acosSlbSmppS 37 } 

		msgProxyParseMsgFail OBJECT-TYPE
		SYNTAX  CounterBasedGauge64 
		MAX-ACCESS read-only 
		STATUS current
		DESCRIPTION  "" 
		::={ acosSlbSmppS 38 } 

		msgProxyProcessMsgFail OBJECT-TYPE
		SYNTAX  CounterBasedGauge64 
		MAX-ACCESS read-only 
		STATUS current
		DESCRIPTION  "" 
		::={ acosSlbSmppS 39 } 

		msgProxyNoVport OBJECT-TYPE
		SYNTAX  CounterBasedGauge64 
		MAX-ACCESS read-only 
		STATUS current
		DESCRIPTION  "" 
		::={ acosSlbSmppS 40 } 

		msgProxyFailSelectServer OBJECT-TYPE
		SYNTAX  CounterBasedGauge64 
		MAX-ACCESS read-only 
		STATUS current
		DESCRIPTION  "" 
		::={ acosSlbSmppS 41 } 

		msgProxyFailAllocMem OBJECT-TYPE
		SYNTAX  CounterBasedGauge64 
		MAX-ACCESS read-only 
		STATUS current
		DESCRIPTION  "" 
		::={ acosSlbSmppS 42 } 

		msgProxyUnexpectedErr OBJECT-TYPE
		SYNTAX  CounterBasedGauge64 
		MAX-ACCESS read-only 
		STATUS current
		DESCRIPTION  "" 
		::={ acosSlbSmppS 43 } 

		msgProxyL7CpuFailed OBJECT-TYPE
		SYNTAX  CounterBasedGauge64 
		MAX-ACCESS read-only 
		STATUS current
		DESCRIPTION  "" 
		::={ acosSlbSmppS 44 } 

		msgProxyL4ToL7 OBJECT-TYPE
		SYNTAX  CounterBasedGauge64 
		MAX-ACCESS read-only 
		STATUS current
		DESCRIPTION  "" 
		::={ acosSlbSmppS 45 } 

		msgProxyL4FromL7 OBJECT-TYPE
		SYNTAX  CounterBasedGauge64 
		MAX-ACCESS read-only 
		STATUS current
		DESCRIPTION  "" 
		::={ acosSlbSmppS 46 } 

		msgProxyToL4SendPkt OBJECT-TYPE
		SYNTAX  CounterBasedGauge64 
		MAX-ACCESS read-only 
		STATUS current
		DESCRIPTION  "" 
		::={ acosSlbSmppS 47 } 

		msgProxyL4FromL4Send OBJECT-TYPE
		SYNTAX  CounterBasedGauge64 
		MAX-ACCESS read-only 
		STATUS current
		DESCRIPTION  "" 
		::={ acosSlbSmppS 48 } 

		msgProxyL7ToL4 OBJECT-TYPE
		SYNTAX  CounterBasedGauge64 
		MAX-ACCESS read-only 
		STATUS current
		DESCRIPTION  "" 
		::={ acosSlbSmppS 49 } 

		msgProxyMagBack OBJECT-TYPE
		SYNTAX  CounterBasedGauge64 
		MAX-ACCESS read-only 
		STATUS current
		DESCRIPTION  "" 
		::={ acosSlbSmppS 50 } 

		msgProxyFailDcmsg OBJECT-TYPE
		SYNTAX  CounterBasedGauge64 
		MAX-ACCESS read-only 
		STATUS current
		DESCRIPTION  "" 
		::={ acosSlbSmppS 51 } 

		msgProxyDeprecatedConn OBJECT-TYPE
		SYNTAX  CounterBasedGauge64 
		MAX-ACCESS read-only 
		STATUS current
		DESCRIPTION  "" 
		::={ acosSlbSmppS 52 } 

		msgProxyHoldMsg OBJECT-TYPE
		SYNTAX  CounterBasedGauge64 
		MAX-ACCESS read-only 
		STATUS current
		DESCRIPTION  "" 
		::={ acosSlbSmppS 53 } 

		msgProxySplitPkt OBJECT-TYPE
		SYNTAX  CounterBasedGauge64 
		MAX-ACCESS read-only 
		STATUS current
		DESCRIPTION  "" 
		::={ acosSlbSmppS 54 } 

		msgProxyPiplineMsg OBJECT-TYPE
		SYNTAX  CounterBasedGauge64 
		MAX-ACCESS read-only 
		STATUS current
		DESCRIPTION  "" 
		::={ acosSlbSmppS 55 } 

		msgProxyClientReset OBJECT-TYPE
		SYNTAX  CounterBasedGauge64 
		MAX-ACCESS read-only 
		STATUS current
		DESCRIPTION  "" 
		::={ acosSlbSmppS 56 } 

		msgProxyServerReset OBJECT-TYPE
		SYNTAX  CounterBasedGauge64 
		MAX-ACCESS read-only 
		STATUS current
		DESCRIPTION  "" 
		::={ acosSlbSmppS 57 } 

		payloadAllocd OBJECT-TYPE
		SYNTAX  CounterBasedGauge64 
		MAX-ACCESS read-only 
		STATUS current
		DESCRIPTION  "" 
		::={ acosSlbSmppS 58 } 

		payloadFreed OBJECT-TYPE
		SYNTAX  CounterBasedGauge64 
		MAX-ACCESS read-only 
		STATUS current
		DESCRIPTION  "" 
		::={ acosSlbSmppS 59 } 

		pktTooSmall OBJECT-TYPE
		SYNTAX  CounterBasedGauge64 
		MAX-ACCESS read-only 
		STATUS current
		DESCRIPTION  "" 
		::={ acosSlbSmppS 60 } 

		invalidSeq OBJECT-TYPE
		SYNTAX  CounterBasedGauge64 
		MAX-ACCESS read-only 
		STATUS current
		DESCRIPTION  "" 
		::={ acosSlbSmppS 61 } 

		acosRespDirectly OBJECT-TYPE
		SYNTAX  CounterBasedGauge64 
		MAX-ACCESS read-only 
		STATUS current
		DESCRIPTION  "Number of packet which AX responds directly" 
		::={ acosSlbSmppS 62 } 

		selectClientConn OBJECT-TYPE
		SYNTAX  CounterBasedGauge64 
		MAX-ACCESS read-only 
		STATUS current
		DESCRIPTION  "Client conn selection" 
		::={ acosSlbSmppS 63 } 

		selectClientByReq OBJECT-TYPE
		SYNTAX  CounterBasedGauge64 
		MAX-ACCESS read-only 
		STATUS current
		DESCRIPTION  "Select by request" 
		::={ acosSlbSmppS 64 } 

		selectClientFromList OBJECT-TYPE
		SYNTAX  CounterBasedGauge64 
		MAX-ACCESS read-only 
		STATUS current
		DESCRIPTION  "Select by roundbin" 
		::={ acosSlbSmppS 65 } 

		selectClientByConn OBJECT-TYPE
		SYNTAX  CounterBasedGauge64 
		MAX-ACCESS read-only 
		STATUS current
		DESCRIPTION  "Select by conn" 
		::={ acosSlbSmppS 66 } 

		selectClientFail OBJECT-TYPE
		SYNTAX  CounterBasedGauge64 
		MAX-ACCESS read-only 
		STATUS current
		DESCRIPTION  "Select failed" 
		::={ acosSlbSmppS 67 } 

		selectServerConn OBJECT-TYPE
		SYNTAX  CounterBasedGauge64 
		MAX-ACCESS read-only 
		STATUS current
		DESCRIPTION  "Server conn selection" 
		::={ acosSlbSmppS 68 } 

		selectServerByReq OBJECT-TYPE
		SYNTAX  CounterBasedGauge64 
		MAX-ACCESS read-only 
		STATUS current
		DESCRIPTION  "Select by request" 
		::={ acosSlbSmppS 69 } 

		selectServerFromList OBJECT-TYPE
		SYNTAX  CounterBasedGauge64 
		MAX-ACCESS read-only 
		STATUS current
		DESCRIPTION  "Select by roundbin" 
		::={ acosSlbSmppS 70 } 

		selectServerByConn OBJECT-TYPE
		SYNTAX  CounterBasedGauge64 
		MAX-ACCESS read-only 
		STATUS current
		DESCRIPTION  "Select server conn by client conn" 
		::={ acosSlbSmppS 71 } 

		selectServerFail OBJECT-TYPE
		SYNTAX  CounterBasedGauge64 
		MAX-ACCESS read-only 
		STATUS current
		DESCRIPTION  "Fail to select server conn" 
		::={ acosSlbSmppS 72 } 

		bindConn OBJECT-TYPE
		SYNTAX  CounterBasedGauge64 
		MAX-ACCESS read-only 
		STATUS current
		DESCRIPTION  "" 
		::={ acosSlbSmppS 73 } 

		unbindConn OBJECT-TYPE
		SYNTAX  CounterBasedGauge64 
		MAX-ACCESS read-only 
		STATUS current
		DESCRIPTION  "" 
		::={ acosSlbSmppS 74 } 

		enquireLinkRecv OBJECT-TYPE
		SYNTAX  CounterBasedGauge64 
		MAX-ACCESS read-only 
		STATUS current
		DESCRIPTION  "" 
		::={ acosSlbSmppS 75 } 

		enquireLinkRespRecv OBJECT-TYPE
		SYNTAX  CounterBasedGauge64 
		MAX-ACCESS read-only 
		STATUS current
		DESCRIPTION  "" 
		::={ acosSlbSmppS 76 } 

		enquireLinkSend OBJECT-TYPE
		SYNTAX  CounterBasedGauge64 
		MAX-ACCESS read-only 
		STATUS current
		DESCRIPTION  "" 
		::={ acosSlbSmppS 77 } 

		enquireLinkRespSend OBJECT-TYPE
		SYNTAX  CounterBasedGauge64 
		MAX-ACCESS read-only 
		STATUS current
		DESCRIPTION  "" 
		::={ acosSlbSmppS 78 } 

		clientConnPutInList OBJECT-TYPE
		SYNTAX  CounterBasedGauge64 
		MAX-ACCESS read-only 
		STATUS current
		DESCRIPTION  "" 
		::={ acosSlbSmppS 79 } 

		clientConnGetFromList OBJECT-TYPE
		SYNTAX  CounterBasedGauge64 
		MAX-ACCESS read-only 
		STATUS current
		DESCRIPTION  "" 
		::={ acosSlbSmppS 80 } 

		serverConnPutInList OBJECT-TYPE
		SYNTAX  CounterBasedGauge64 
		MAX-ACCESS read-only 
		STATUS current
		DESCRIPTION  "" 
		::={ acosSlbSmppS 81 } 

		serverConnGetFromList OBJECT-TYPE
		SYNTAX  CounterBasedGauge64 
		MAX-ACCESS read-only 
		STATUS current
		DESCRIPTION  "" 
		::={ acosSlbSmppS 82 } 

		serverConnFailBind OBJECT-TYPE
		SYNTAX  CounterBasedGauge64 
		MAX-ACCESS read-only 
		STATUS current
		DESCRIPTION  "" 
		::={ acosSlbSmppS 83 } 

		singleMsg OBJECT-TYPE
		SYNTAX  CounterBasedGauge64 
		MAX-ACCESS read-only 
		STATUS current
		DESCRIPTION  "" 
		::={ acosSlbSmppS 84 } 

		failBindMsg OBJECT-TYPE
		SYNTAX  CounterBasedGauge64 
		MAX-ACCESS read-only 
		STATUS current
		DESCRIPTION  "" 
		::={ acosSlbSmppS 85 } 

acosSlbSmtp                         OBJECT IDENTIFIER ::= { acosSlb 30 }
acosSlbSmtpS                        OBJECT IDENTIFIER ::= { acosSlbSmtp 1 }

		slbSmtpCurrProxy OBJECT-TYPE
		SYNTAX  CounterBasedGauge64 
		MAX-ACCESS read-only 
		STATUS current
		DESCRIPTION  "Current proxy conns" 
		::={ acosSlbSmtpS 1 } 

		slbSmtpTotalProxy OBJECT-TYPE
		SYNTAX  CounterBasedGauge64 
		MAX-ACCESS read-only 
		STATUS current
		DESCRIPTION  "Total proxy conns" 
		::={ acosSlbSmtpS 2 } 

		slbSmtpRequest OBJECT-TYPE
		SYNTAX  CounterBasedGauge64 
		MAX-ACCESS read-only 
		STATUS current
		DESCRIPTION  "SMTP requests" 
		::={ acosSlbSmtpS 3 } 

		requestSuccess OBJECT-TYPE
		SYNTAX  CounterBasedGauge64 
		MAX-ACCESS read-only 
		STATUS current
		DESCRIPTION  "SMTP requests (success)" 
		::={ acosSlbSmtpS 4 } 

		noProxy OBJECT-TYPE
		SYNTAX  CounterBasedGauge64 
		MAX-ACCESS read-only 
		STATUS current
		DESCRIPTION  "No proxy error" 
		::={ acosSlbSmtpS 5 } 

		clientReset OBJECT-TYPE
		SYNTAX  CounterBasedGauge64 
		MAX-ACCESS read-only 
		STATUS current
		DESCRIPTION  "Client reset" 
		::={ acosSlbSmtpS 6 } 

		serverReset OBJECT-TYPE
		SYNTAX  CounterBasedGauge64 
		MAX-ACCESS read-only 
		STATUS current
		DESCRIPTION  "Server reset" 
		::={ acosSlbSmtpS 7 } 

		noTuple OBJECT-TYPE
		SYNTAX  CounterBasedGauge64 
		MAX-ACCESS read-only 
		STATUS current
		DESCRIPTION  "No tuple error" 
		::={ acosSlbSmtpS 8 } 

		parseReqFail OBJECT-TYPE
		SYNTAX  CounterBasedGauge64 
		MAX-ACCESS read-only 
		STATUS current
		DESCRIPTION  "Parse request failure" 
		::={ acosSlbSmtpS 9 } 

		serverSelectFail OBJECT-TYPE
		SYNTAX  CounterBasedGauge64 
		MAX-ACCESS read-only 
		STATUS current
		DESCRIPTION  "Server selection failure" 
		::={ acosSlbSmtpS 10 } 

		forwardReqFail OBJECT-TYPE
		SYNTAX  CounterBasedGauge64 
		MAX-ACCESS read-only 
		STATUS current
		DESCRIPTION  "Forward request failure" 
		::={ acosSlbSmtpS 11 } 

		forwardReqDataFail OBJECT-TYPE
		SYNTAX  CounterBasedGauge64 
		MAX-ACCESS read-only 
		STATUS current
		DESCRIPTION  "Forward REQ data failure" 
		::={ acosSlbSmtpS 12 } 

		reqRetran OBJECT-TYPE
		SYNTAX  CounterBasedGauge64 
		MAX-ACCESS read-only 
		STATUS current
		DESCRIPTION  "Request retransmit" 
		::={ acosSlbSmtpS 13 } 

		reqOfo OBJECT-TYPE
		SYNTAX  CounterBasedGauge64 
		MAX-ACCESS read-only 
		STATUS current
		DESCRIPTION  "Request pkt out-of-order" 
		::={ acosSlbSmtpS 14 } 

		serverReselect OBJECT-TYPE
		SYNTAX  CounterBasedGauge64 
		MAX-ACCESS read-only 
		STATUS current
		DESCRIPTION  "Server reselection" 
		::={ acosSlbSmtpS 15 } 

		serverPremClose OBJECT-TYPE
		SYNTAX  CounterBasedGauge64 
		MAX-ACCESS read-only 
		STATUS current
		DESCRIPTION  "Server premature close" 
		::={ acosSlbSmtpS 16 } 

		newServerConn OBJECT-TYPE
		SYNTAX  CounterBasedGauge64 
		MAX-ACCESS read-only 
		STATUS current
		DESCRIPTION  "Server connection made" 
		::={ acosSlbSmtpS 17 } 

		slbSmtpSnatFail OBJECT-TYPE
		SYNTAX  CounterBasedGauge64 
		MAX-ACCESS read-only 
		STATUS current
		DESCRIPTION  "Source NAT failure" 
		::={ acosSlbSmtpS 18 } 

		tcpOutReset OBJECT-TYPE
		SYNTAX  CounterBasedGauge64 
		MAX-ACCESS read-only 
		STATUS current
		DESCRIPTION  "TCP out reset" 
		::={ acosSlbSmtpS 19 } 

		aflexSwitched OBJECT-TYPE
		SYNTAX  CounterBasedGauge64 
		MAX-ACCESS read-only 
		STATUS current
		DESCRIPTION  "aFleX switching" 
		::={ acosSlbSmtpS 20 } 

		aflexSwitchedOk OBJECT-TYPE
		SYNTAX  CounterBasedGauge64 
		MAX-ACCESS read-only 
		STATUS current
		DESCRIPTION  "aFleX switching (succ)" 
		::={ acosSlbSmtpS 21 } 

		recvClientCommandEHLO OBJECT-TYPE
		SYNTAX  CounterBasedGauge64 
		MAX-ACCESS read-only 
		STATUS current
		DESCRIPTION  "Recv client EHLO" 
		::={ acosSlbSmtpS 22 } 

		recvClientCommandHELO OBJECT-TYPE
		SYNTAX  CounterBasedGauge64 
		MAX-ACCESS read-only 
		STATUS current
		DESCRIPTION  "Recv client HELO" 
		::={ acosSlbSmtpS 23 } 

		recvClientCommandMAIL OBJECT-TYPE
		SYNTAX  CounterBasedGauge64 
		MAX-ACCESS read-only 
		STATUS current
		DESCRIPTION  "Recv client MAIL" 
		::={ acosSlbSmtpS 24 } 

		recvClientCommandRCPT OBJECT-TYPE
		SYNTAX  CounterBasedGauge64 
		MAX-ACCESS read-only 
		STATUS current
		DESCRIPTION  "Recv client RCPT" 
		::={ acosSlbSmtpS 25 } 

		recvClientCommandDATA OBJECT-TYPE
		SYNTAX  CounterBasedGauge64 
		MAX-ACCESS read-only 
		STATUS current
		DESCRIPTION  "Recv client DATA" 
		::={ acosSlbSmtpS 26 } 

		recvClientCommandRSET OBJECT-TYPE
		SYNTAX  CounterBasedGauge64 
		MAX-ACCESS read-only 
		STATUS current
		DESCRIPTION  "Recv client RSET" 
		::={ acosSlbSmtpS 27 } 

		recvClientCommandVRFY OBJECT-TYPE
		SYNTAX  CounterBasedGauge64 
		MAX-ACCESS read-only 
		STATUS current
		DESCRIPTION  "Recv client VRFY" 
		::={ acosSlbSmtpS 28 } 

		recvClientCommandEXPN OBJECT-TYPE
		SYNTAX  CounterBasedGauge64 
		MAX-ACCESS read-only 
		STATUS current
		DESCRIPTION  "Recv client EXPN" 
		::={ acosSlbSmtpS 29 } 

		recvClientCommandHELP OBJECT-TYPE
		SYNTAX  CounterBasedGauge64 
		MAX-ACCESS read-only 
		STATUS current
		DESCRIPTION  "Recv client HELP" 
		::={ acosSlbSmtpS 30 } 

		recvClientCommandNOOP OBJECT-TYPE
		SYNTAX  CounterBasedGauge64 
		MAX-ACCESS read-only 
		STATUS current
		DESCRIPTION  "Recv client NOOP" 
		::={ acosSlbSmtpS 31 } 

		recvClientCommandQUIT OBJECT-TYPE
		SYNTAX  CounterBasedGauge64 
		MAX-ACCESS read-only 
		STATUS current
		DESCRIPTION  "Recv client QUIT" 
		::={ acosSlbSmtpS 32 } 

		recvClientCommandSTARTTLS OBJECT-TYPE
		SYNTAX  CounterBasedGauge64 
		MAX-ACCESS read-only 
		STATUS current
		DESCRIPTION  "Recv client STARTTLS" 
		::={ acosSlbSmtpS 33 } 

		recvClientCommandOthers OBJECT-TYPE
		SYNTAX  CounterBasedGauge64 
		MAX-ACCESS read-only 
		STATUS current
		DESCRIPTION  "Recv client other cmds" 
		::={ acosSlbSmtpS 34 } 

		sendClientServiceReady OBJECT-TYPE
		SYNTAX  CounterBasedGauge64 
		MAX-ACCESS read-only 
		STATUS current
		DESCRIPTION  "Sent client serv-rdy" 
		::={ acosSlbSmtpS 35 } 

		sendClientServiceNotReady OBJECT-TYPE
		SYNTAX  CounterBasedGauge64 
		MAX-ACCESS read-only 
		STATUS current
		DESCRIPTION  "Sent client serv-not-rdy" 
		::={ acosSlbSmtpS 36 } 

		sendClientCloseConnection OBJECT-TYPE
		SYNTAX  CounterBasedGauge64 
		MAX-ACCESS read-only 
		STATUS current
		DESCRIPTION  "Sent client close-conn" 
		::={ acosSlbSmtpS 37 } 

		sendClientGoAhead OBJECT-TYPE
		SYNTAX  CounterBasedGauge64 
		MAX-ACCESS read-only 
		STATUS current
		DESCRIPTION  "Sent client go-ahead" 
		::={ acosSlbSmtpS 38 } 

		sendClientStartTLSFirst OBJECT-TYPE
		SYNTAX  CounterBasedGauge64 
		MAX-ACCESS read-only 
		STATUS current
		DESCRIPTION  "Sent client STARTTLS-1st" 
		::={ acosSlbSmtpS 39 } 

		sendClientTLSNotAvailable OBJECT-TYPE
		SYNTAX  CounterBasedGauge64 
		MAX-ACCESS read-only 
		STATUS current
		DESCRIPTION  "Sent client TLS-not-aval" 
		::={ acosSlbSmtpS 40 } 

		sendClientNoCommand OBJECT-TYPE
		SYNTAX  CounterBasedGauge64 
		MAX-ACCESS read-only 
		STATUS current
		DESCRIPTION  "Sent client no-such-cmd" 
		::={ acosSlbSmtpS 41 } 

		sendServerCmdReset OBJECT-TYPE
		SYNTAX  CounterBasedGauge64 
		MAX-ACCESS read-only 
		STATUS current
		DESCRIPTION  "Sent server RSET" 
		::={ acosSlbSmtpS 42 } 

		tlsEstablished OBJECT-TYPE
		SYNTAX  CounterBasedGauge64 
		MAX-ACCESS read-only 
		STATUS current
		DESCRIPTION  "SSL session established" 
		::={ acosSlbSmtpS 43 } 

		l4Switched OBJECT-TYPE
		SYNTAX  CounterBasedGauge64 
		MAX-ACCESS read-only 
		STATUS current
		DESCRIPTION  "L4 switching" 
		::={ acosSlbSmtpS 44 } 

		recvServerServiceNotReady OBJECT-TYPE
		SYNTAX  CounterBasedGauge64 
		MAX-ACCESS read-only 
		STATUS current
		DESCRIPTION  "Recv server serv-not-rdy" 
		::={ acosSlbSmtpS 45 } 

		recvServerUnknowReplyCode OBJECT-TYPE
		SYNTAX  CounterBasedGauge64 
		MAX-ACCESS read-only 
		STATUS current
		DESCRIPTION  "Recv server unknown-code" 
		::={ acosSlbSmtpS 46 } 

		clientDomainSwitch OBJECT-TYPE
		SYNTAX  CounterBasedGauge64 
		MAX-ACCESS read-only 
		STATUS current
		DESCRIPTION  "Client domain switching" 
		::={ acosSlbSmtpS 47 } 

		clientDomainSwitchOk OBJECT-TYPE
		SYNTAX  CounterBasedGauge64 
		MAX-ACCESS read-only 
		STATUS current
		DESCRIPTION  "Client domain sw (succ)" 
		::={ acosSlbSmtpS 48 } 

		lbSwitch OBJECT-TYPE
		SYNTAX  CounterBasedGauge64 
		MAX-ACCESS read-only 
		STATUS current
		DESCRIPTION  "LB switching" 
		::={ acosSlbSmtpS 49 } 

		lbSwitchOk OBJECT-TYPE
		SYNTAX  CounterBasedGauge64 
		MAX-ACCESS read-only 
		STATUS current
		DESCRIPTION  "LB switching (succ)" 
		::={ acosSlbSmtpS 50 } 

		readRequestLineFail OBJECT-TYPE
		SYNTAX  CounterBasedGauge64 
		MAX-ACCESS read-only 
		STATUS current
		DESCRIPTION  "Read request line fail" 
		::={ acosSlbSmtpS 51 } 

		getAllHeadersFail OBJECT-TYPE
		SYNTAX  CounterBasedGauge64 
		MAX-ACCESS read-only 
		STATUS current
		DESCRIPTION  "Get all headers fail" 
		::={ acosSlbSmtpS 52 } 

		tooManyHeaders OBJECT-TYPE
		SYNTAX  CounterBasedGauge64 
		MAX-ACCESS read-only 
		STATUS current
		DESCRIPTION  "Too many headers" 
		::={ acosSlbSmtpS 53 } 

		lineTooLong OBJECT-TYPE
		SYNTAX  CounterBasedGauge64 
		MAX-ACCESS read-only 
		STATUS current
		DESCRIPTION  "Line too long" 
		::={ acosSlbSmtpS 54 } 

		lineAcrossPacket OBJECT-TYPE
		SYNTAX  CounterBasedGauge64 
		MAX-ACCESS read-only 
		STATUS current
		DESCRIPTION  "Line across packets" 
		::={ acosSlbSmtpS 55 } 

		lineExtend OBJECT-TYPE
		SYNTAX  CounterBasedGauge64 
		MAX-ACCESS read-only 
		STATUS current
		DESCRIPTION  "Line extend" 
		::={ acosSlbSmtpS 56 } 

		lineExtendFail OBJECT-TYPE
		SYNTAX  CounterBasedGauge64 
		MAX-ACCESS read-only 
		STATUS current
		DESCRIPTION  "Line extend fail" 
		::={ acosSlbSmtpS 57 } 

		lineTableExtend OBJECT-TYPE
		SYNTAX  CounterBasedGauge64 
		MAX-ACCESS read-only 
		STATUS current
		DESCRIPTION  "Table extend" 
		::={ acosSlbSmtpS 58 } 

		lineTableExtendFail OBJECT-TYPE
		SYNTAX  CounterBasedGauge64 
		MAX-ACCESS read-only 
		STATUS current
		DESCRIPTION  "Table extend fail" 
		::={ acosSlbSmtpS 59 } 

		parseRequestLineFail OBJECT-TYPE
		SYNTAX  CounterBasedGauge64 
		MAX-ACCESS read-only 
		STATUS current
		DESCRIPTION  "Parse request line fail" 
		::={ acosSlbSmtpS 60 } 

		insertResonseLineFail OBJECT-TYPE
		SYNTAX  CounterBasedGauge64 
		MAX-ACCESS read-only 
		STATUS current
		DESCRIPTION  "Ins response line fail" 
		::={ acosSlbSmtpS 61 } 

		removeResonseLineFail OBJECT-TYPE
		SYNTAX  CounterBasedGauge64 
		MAX-ACCESS read-only 
		STATUS current
		DESCRIPTION  "Del response line fail" 
		::={ acosSlbSmtpS 62 } 

		parseResonseLineFail OBJECT-TYPE
		SYNTAX  CounterBasedGauge64 
		MAX-ACCESS read-only 
		STATUS current
		DESCRIPTION  "Parse response line fail" 
		::={ acosSlbSmtpS 63 } 

		aflexLbReselect OBJECT-TYPE
		SYNTAX  CounterBasedGauge64 
		MAX-ACCESS read-only 
		STATUS current
		DESCRIPTION  "aFleX lb reselect" 
		::={ acosSlbSmtpS 64 } 

		aflexLbReselectOk OBJECT-TYPE
		SYNTAX  CounterBasedGauge64 
		MAX-ACCESS read-only 
		STATUS current
		DESCRIPTION  "aFleX lb reselect (succ)" 
		::={ acosSlbSmtpS 65 } 

		serverSTARTTLSInit OBJECT-TYPE
		SYNTAX  CounterBasedGauge64 
		MAX-ACCESS read-only 
		STATUS current
		DESCRIPTION  "Init server side STARTTLS" 
		::={ acosSlbSmtpS 66 } 

		serverSTARTTLSFail OBJECT-TYPE
		SYNTAX  CounterBasedGauge64 
		MAX-ACCESS read-only 
		STATUS current
		DESCRIPTION  "Server side STARTTLS fail" 
		::={ acosSlbSmtpS 67 } 

		rserverSTARTTLSDisable OBJECT-TYPE
		SYNTAX  CounterBasedGauge64 
		MAX-ACCESS read-only 
		STATUS current
		DESCRIPTION  "real server not support STARTTLS" 
		::={ acosSlbSmtpS 68 } 

		recvClientCommandTURN OBJECT-TYPE
		SYNTAX  CounterBasedGauge64 
		MAX-ACCESS read-only 
		STATUS current
		DESCRIPTION  "Recv client TURN" 
		::={ acosSlbSmtpS 69 } 

		recvClientCommandETRN OBJECT-TYPE
		SYNTAX  CounterBasedGauge64 
		MAX-ACCESS read-only 
		STATUS current
		DESCRIPTION  "Recv client ETRN" 
		::={ acosSlbSmtpS 70 } 

		sendServerEhlo OBJECT-TYPE
		SYNTAX  CounterBasedGauge64 
		MAX-ACCESS read-only 
		STATUS current
		DESCRIPTION  "Proxy sends server EHLO" 
		::={ acosSlbSmtpS 71 } 

		failToSaveClientEhlo OBJECT-TYPE
		SYNTAX  CounterBasedGauge64 
		MAX-ACCESS read-only 
		STATUS current
		DESCRIPTION  "Failed to save client EHLO" 
		::={ acosSlbSmtpS 72 } 

		aflexMailFail OBJECT-TYPE
		SYNTAX  CounterBasedGauge64 
		MAX-ACCESS read-only 
		STATUS current
		DESCRIPTION  "aFlex Mail event failed" 
		::={ acosSlbSmtpS 73 } 

		dropServerEhloOk OBJECT-TYPE
		SYNTAX  CounterBasedGauge64 
		MAX-ACCESS read-only 
		STATUS current
		DESCRIPTION  "Server EHLO_OK dropped" 
		::={ acosSlbSmtpS 74 } 

		clientEhloSaved OBJECT-TYPE
		SYNTAX  CounterBasedGauge64 
		MAX-ACCESS read-only 
		STATUS current
		DESCRIPTION  "Client EHLO saved" 
		::={ acosSlbSmtpS 75 } 

acosSlbMqtt                         OBJECT IDENTIFIER ::= { acosSlb 77 }
acosSlbMqttS                        OBJECT IDENTIFIER ::= { acosSlbMqtt 1 }

		recvMqttConnect OBJECT-TYPE
		SYNTAX  CounterBasedGauge64 
		MAX-ACCESS read-only 
		STATUS current
		DESCRIPTION  "MQTT Connect" 
		::={ acosSlbMqttS 1 } 

		recvMqttConnack OBJECT-TYPE
		SYNTAX  CounterBasedGauge64 
		MAX-ACCESS read-only 
		STATUS current
		DESCRIPTION  "MQTT Connack" 
		::={ acosSlbMqttS 2 } 

		recvMqttPublish OBJECT-TYPE
		SYNTAX  CounterBasedGauge64 
		MAX-ACCESS read-only 
		STATUS current
		DESCRIPTION  "MQTT Publish" 
		::={ acosSlbMqttS 3 } 

		recvMqttPuback OBJECT-TYPE
		SYNTAX  CounterBasedGauge64 
		MAX-ACCESS read-only 
		STATUS current
		DESCRIPTION  "MQTT Puback" 
		::={ acosSlbMqttS 4 } 

		recvMqttPubrec OBJECT-TYPE
		SYNTAX  CounterBasedGauge64 
		MAX-ACCESS read-only 
		STATUS current
		DESCRIPTION  "MQTT Pubrec" 
		::={ acosSlbMqttS 5 } 

		recvMqttPubrel OBJECT-TYPE
		SYNTAX  CounterBasedGauge64 
		MAX-ACCESS read-only 
		STATUS current
		DESCRIPTION  "MQTT Pubrel" 
		::={ acosSlbMqttS 6 } 

		recvMqttPubcomp OBJECT-TYPE
		SYNTAX  CounterBasedGauge64 
		MAX-ACCESS read-only 
		STATUS current
		DESCRIPTION  "MQTT Pubcomp" 
		::={ acosSlbMqttS 7 } 

		recvMqttSubscribe OBJECT-TYPE
		SYNTAX  CounterBasedGauge64 
		MAX-ACCESS read-only 
		STATUS current
		DESCRIPTION  "MQTT Subscribe" 
		::={ acosSlbMqttS 8 } 

		recvMqttSuback OBJECT-TYPE
		SYNTAX  CounterBasedGauge64 
		MAX-ACCESS read-only 
		STATUS current
		DESCRIPTION  "MQTT Suback" 
		::={ acosSlbMqttS 9 } 

		recvMqttUnsubscribe OBJECT-TYPE
		SYNTAX  CounterBasedGauge64 
		MAX-ACCESS read-only 
		STATUS current
		DESCRIPTION  "MQTT Unsubscribe" 
		::={ acosSlbMqttS 10 } 

		recvMqttUnsuback OBJECT-TYPE
		SYNTAX  CounterBasedGauge64 
		MAX-ACCESS read-only 
		STATUS current
		DESCRIPTION  "MQTT Unsuback" 
		::={ acosSlbMqttS 11 } 

		recvMqttPingreq OBJECT-TYPE
		SYNTAX  CounterBasedGauge64 
		MAX-ACCESS read-only 
		STATUS current
		DESCRIPTION  "MQTT Pingreq" 
		::={ acosSlbMqttS 12 } 

		recvMqttPingresp OBJECT-TYPE
		SYNTAX  CounterBasedGauge64 
		MAX-ACCESS read-only 
		STATUS current
		DESCRIPTION  "MQTT Pingresp" 
		::={ acosSlbMqttS 13 } 

		recvMqttDisconnect OBJECT-TYPE
		SYNTAX  CounterBasedGauge64 
		MAX-ACCESS read-only 
		STATUS current
		DESCRIPTION  "MQTT Disconnect" 
		::={ acosSlbMqttS 14 } 

		recvMqttAuth OBJECT-TYPE
		SYNTAX  CounterBasedGauge64 
		MAX-ACCESS read-only 
		STATUS current
		DESCRIPTION  "MQTT Auth" 
		::={ acosSlbMqttS 15 } 

		recvMqttOther OBJECT-TYPE
		SYNTAX  CounterBasedGauge64 
		MAX-ACCESS read-only 
		STATUS current
		DESCRIPTION  "MQTT Unknown" 
		::={ acosSlbMqttS 16 } 

		currProxy OBJECT-TYPE
		SYNTAX  CounterBasedGauge64 
		MAX-ACCESS read-only 
		STATUS current
		DESCRIPTION  "Current proxy conns" 
		::={ acosSlbMqttS 17 } 

		totalProxy OBJECT-TYPE
		SYNTAX  CounterBasedGauge64 
		MAX-ACCESS read-only 
		STATUS current
		DESCRIPTION  "Total proxy conns" 
		::={ acosSlbMqttS 18 } 

		request OBJECT-TYPE
		SYNTAX  CounterBasedGauge64 
		MAX-ACCESS read-only 
		STATUS current
		DESCRIPTION  "Total MQTT Commands" 
		::={ acosSlbMqttS 19 } 

		parseConnectFail OBJECT-TYPE
		SYNTAX  CounterBasedGauge64 
		MAX-ACCESS read-only 
		STATUS current
		DESCRIPTION  "Parse connect failure" 
		::={ acosSlbMqttS 20 } 

		parsePublishFail OBJECT-TYPE
		SYNTAX  CounterBasedGauge64 
		MAX-ACCESS read-only 
		STATUS current
		DESCRIPTION  "Parse publish failure" 
		::={ acosSlbMqttS 21 } 

		parseSubscribeFail OBJECT-TYPE
		SYNTAX  CounterBasedGauge64 
		MAX-ACCESS read-only 
		STATUS current
		DESCRIPTION  "Parse subscribe failure" 
		::={ acosSlbMqttS 22 } 

		parseUnsubscribeFail OBJECT-TYPE
		SYNTAX  CounterBasedGauge64 
		MAX-ACCESS read-only 
		STATUS current
		DESCRIPTION  "Parse unsubscribe failure" 
		::={ acosSlbMqttS 23 } 

		tupleNotLinked OBJECT-TYPE
		SYNTAX  CounterBasedGauge64 
		MAX-ACCESS read-only 
		STATUS current
		DESCRIPTION  "tuple-not-linked failure" 
		::={ acosSlbMqttS 24 } 

		tupleAlreadyLinked OBJECT-TYPE
		SYNTAX  CounterBasedGauge64 
		MAX-ACCESS read-only 
		STATUS current
		DESCRIPTION  "tuple-already-linked failure" 
		::={ acosSlbMqttS 25 } 

		connNull OBJECT-TYPE
		SYNTAX  CounterBasedGauge64 
		MAX-ACCESS read-only 
		STATUS current
		DESCRIPTION  "Null conn" 
		::={ acosSlbMqttS 26 } 

		clientIdNull OBJECT-TYPE
		SYNTAX  CounterBasedGauge64 
		MAX-ACCESS read-only 
		STATUS current
		DESCRIPTION  "Null client id" 
		::={ acosSlbMqttS 27 } 

		sessionExist OBJECT-TYPE
		SYNTAX  CounterBasedGauge64 
		MAX-ACCESS read-only 
		STATUS current
		DESCRIPTION  "Session already exist" 
		::={ acosSlbMqttS 28 } 

		insertionFailed OBJECT-TYPE
		SYNTAX  CounterBasedGauge64 
		MAX-ACCESS read-only 
		STATUS current
		DESCRIPTION  "Insertion failure" 
		::={ acosSlbMqttS 29 } 

		insertionSuccessful OBJECT-TYPE
		SYNTAX  CounterBasedGauge64 
		MAX-ACCESS read-only 
		STATUS current
		DESCRIPTION  "Insertion successful" 
		::={ acosSlbMqttS 30 } 

acosSlbIcap                         OBJECT IDENTIFIER ::= { acosSlb 31 }
acosSlbIcapS                        OBJECT IDENTIFIER ::= { acosSlbIcap 1 }

		reqmodRequest OBJECT-TYPE
		SYNTAX  CounterBasedGauge64 
		MAX-ACCESS read-only 
		STATUS current
		DESCRIPTION  "Reqmod Request Stats" 
		::={ acosSlbIcapS 1 } 

		respmodRequest OBJECT-TYPE
		SYNTAX  CounterBasedGauge64 
		MAX-ACCESS read-only 
		STATUS current
		DESCRIPTION  "Respmod Request Stats" 
		::={ acosSlbIcapS 2 } 

		reqmodRequestAfter100 OBJECT-TYPE
		SYNTAX  CounterBasedGauge64 
		MAX-ACCESS read-only 
		STATUS current
		DESCRIPTION  "Reqmod Request Sent After 100 Cont Stats" 
		::={ acosSlbIcapS 3 } 

		respmodRequestAfter100 OBJECT-TYPE
		SYNTAX  CounterBasedGauge64 
		MAX-ACCESS read-only 
		STATUS current
		DESCRIPTION  "Respmod Request Sent After 100 Cont Stats" 
		::={ acosSlbIcapS 4 } 

		reqmodResponse OBJECT-TYPE
		SYNTAX  CounterBasedGauge64 
		MAX-ACCESS read-only 
		STATUS current
		DESCRIPTION  "Reqmod Response Stats" 
		::={ acosSlbIcapS 5 } 

		respmodResponse OBJECT-TYPE
		SYNTAX  CounterBasedGauge64 
		MAX-ACCESS read-only 
		STATUS current
		DESCRIPTION  "Respmod Response Stats" 
		::={ acosSlbIcapS 6 } 

		reqmodResponseAfter100 OBJECT-TYPE
		SYNTAX  CounterBasedGauge64 
		MAX-ACCESS read-only 
		STATUS current
		DESCRIPTION  "Reqmod Response After 100 Cont Stats" 
		::={ acosSlbIcapS 7 } 

		respmodResponseAfter100 OBJECT-TYPE
		SYNTAX  CounterBasedGauge64 
		MAX-ACCESS read-only 
		STATUS current
		DESCRIPTION  "Respmod Response After 100 Cont Stats" 
		::={ acosSlbIcapS 8 } 

		chunkNoAllow204 OBJECT-TYPE
		SYNTAX  CounterBasedGauge64 
		MAX-ACCESS read-only 
		STATUS current
		DESCRIPTION  "Chunk so no Allow 204 Stats" 
		::={ acosSlbIcapS 9 } 

		lenExceedNoAllow204 OBJECT-TYPE
		SYNTAX  CounterBasedGauge64 
		MAX-ACCESS read-only 
		STATUS current
		DESCRIPTION  "Length Exceeded so no Allow 204 Stats" 
		::={ acosSlbIcapS 10 } 

		resultContinue OBJECT-TYPE
		SYNTAX  CounterBasedGauge64 
		MAX-ACCESS read-only 
		STATUS current
		DESCRIPTION  "Result Continue Stats" 
		::={ acosSlbIcapS 11 } 

		resultIcapResponse OBJECT-TYPE
		SYNTAX  CounterBasedGauge64 
		MAX-ACCESS read-only 
		STATUS current
		DESCRIPTION  "Result ICAP Response Stats" 
		::={ acosSlbIcapS 12 } 

		result100Continue OBJECT-TYPE
		SYNTAX  CounterBasedGauge64 
		MAX-ACCESS read-only 
		STATUS current
		DESCRIPTION  "Result 100 Continue Stats" 
		::={ acosSlbIcapS 13 } 

		resultOther OBJECT-TYPE
		SYNTAX  CounterBasedGauge64 
		MAX-ACCESS read-only 
		STATUS current
		DESCRIPTION  "Result Other Stats" 
		::={ acosSlbIcapS 14 } 

		status2xx OBJECT-TYPE
		SYNTAX  CounterBasedGauge64 
		MAX-ACCESS read-only 
		STATUS current
		DESCRIPTION  "Status 2xx Stats" 
		::={ acosSlbIcapS 15 } 

		status200 OBJECT-TYPE
		SYNTAX  CounterBasedGauge64 
		MAX-ACCESS read-only 
		STATUS current
		DESCRIPTION  "Status 200 Stats" 
		::={ acosSlbIcapS 16 } 

		status201 OBJECT-TYPE
		SYNTAX  CounterBasedGauge64 
		MAX-ACCESS read-only 
		STATUS current
		DESCRIPTION  "Status 201 Stats" 
		::={ acosSlbIcapS 17 } 

		status202 OBJECT-TYPE
		SYNTAX  CounterBasedGauge64 
		MAX-ACCESS read-only 
		STATUS current
		DESCRIPTION  "Status 202 Stats" 
		::={ acosSlbIcapS 18 } 

		status203 OBJECT-TYPE
		SYNTAX  CounterBasedGauge64 
		MAX-ACCESS read-only 
		STATUS current
		DESCRIPTION  "Status 203 Stats" 
		::={ acosSlbIcapS 19 } 

		status204 OBJECT-TYPE
		SYNTAX  CounterBasedGauge64 
		MAX-ACCESS read-only 
		STATUS current
		DESCRIPTION  "Status 204 Stats" 
		::={ acosSlbIcapS 20 } 

		status205 OBJECT-TYPE
		SYNTAX  CounterBasedGauge64 
		MAX-ACCESS read-only 
		STATUS current
		DESCRIPTION  "Status 205 Stats" 
		::={ acosSlbIcapS 21 } 

		status206 OBJECT-TYPE
		SYNTAX  CounterBasedGauge64 
		MAX-ACCESS read-only 
		STATUS current
		DESCRIPTION  "Status 206 Stats" 
		::={ acosSlbIcapS 22 } 

		status207 OBJECT-TYPE
		SYNTAX  CounterBasedGauge64 
		MAX-ACCESS read-only 
		STATUS current
		DESCRIPTION  "Status 207 Stats" 
		::={ acosSlbIcapS 23 } 

		status1xx OBJECT-TYPE
		SYNTAX  CounterBasedGauge64 
		MAX-ACCESS read-only 
		STATUS current
		DESCRIPTION  "Status 1xx Stats" 
		::={ acosSlbIcapS 24 } 

		status100 OBJECT-TYPE
		SYNTAX  CounterBasedGauge64 
		MAX-ACCESS read-only 
		STATUS current
		DESCRIPTION  "Status 100 Stats" 
		::={ acosSlbIcapS 25 } 

		status101 OBJECT-TYPE
		SYNTAX  CounterBasedGauge64 
		MAX-ACCESS read-only 
		STATUS current
		DESCRIPTION  "Status 101 Stats" 
		::={ acosSlbIcapS 26 } 

		status102 OBJECT-TYPE
		SYNTAX  CounterBasedGauge64 
		MAX-ACCESS read-only 
		STATUS current
		DESCRIPTION  "Status 102 Stats" 
		::={ acosSlbIcapS 27 } 

		status3xx OBJECT-TYPE
		SYNTAX  CounterBasedGauge64 
		MAX-ACCESS read-only 
		STATUS current
		DESCRIPTION  "Status 3xx Stats" 
		::={ acosSlbIcapS 28 } 

		status300 OBJECT-TYPE
		SYNTAX  CounterBasedGauge64 
		MAX-ACCESS read-only 
		STATUS current
		DESCRIPTION  "Status 300 Stats" 
		::={ acosSlbIcapS 29 } 

		status301 OBJECT-TYPE
		SYNTAX  CounterBasedGauge64 
		MAX-ACCESS read-only 
		STATUS current
		DESCRIPTION  "Status 301 Stats" 
		::={ acosSlbIcapS 30 } 

		status302 OBJECT-TYPE
		SYNTAX  CounterBasedGauge64 
		MAX-ACCESS read-only 
		STATUS current
		DESCRIPTION  "Status 302 Stats" 
		::={ acosSlbIcapS 31 } 

		status303 OBJECT-TYPE
		SYNTAX  CounterBasedGauge64 
		MAX-ACCESS read-only 
		STATUS current
		DESCRIPTION  "Status 303 Stats" 
		::={ acosSlbIcapS 32 } 

		status304 OBJECT-TYPE
		SYNTAX  CounterBasedGauge64 
		MAX-ACCESS read-only 
		STATUS current
		DESCRIPTION  "Status 304 Stats" 
		::={ acosSlbIcapS 33 } 

		status305 OBJECT-TYPE
		SYNTAX  CounterBasedGauge64 
		MAX-ACCESS read-only 
		STATUS current
		DESCRIPTION  "Status 305 Stats" 
		::={ acosSlbIcapS 34 } 

		status306 OBJECT-TYPE
		SYNTAX  CounterBasedGauge64 
		MAX-ACCESS read-only 
		STATUS current
		DESCRIPTION  "Status 306 Stats" 
		::={ acosSlbIcapS 35 } 

		status307 OBJECT-TYPE
		SYNTAX  CounterBasedGauge64 
		MAX-ACCESS read-only 
		STATUS current
		DESCRIPTION  "Status 307 Stats" 
		::={ acosSlbIcapS 36 } 

		status4xx OBJECT-TYPE
		SYNTAX  CounterBasedGauge64 
		MAX-ACCESS read-only 
		STATUS current
		DESCRIPTION  "Status 4xx Stats" 
		::={ acosSlbIcapS 37 } 

		status400 OBJECT-TYPE
		SYNTAX  CounterBasedGauge64 
		MAX-ACCESS read-only 
		STATUS current
		DESCRIPTION  "Status 400 Stats" 
		::={ acosSlbIcapS 38 } 

		status401 OBJECT-TYPE
		SYNTAX  CounterBasedGauge64 
		MAX-ACCESS read-only 
		STATUS current
		DESCRIPTION  "Status 401 Stats" 
		::={ acosSlbIcapS 39 } 

		status402 OBJECT-TYPE
		SYNTAX  CounterBasedGauge64 
		MAX-ACCESS read-only 
		STATUS current
		DESCRIPTION  "Status 402 Stats" 
		::={ acosSlbIcapS 40 } 

		status403 OBJECT-TYPE
		SYNTAX  CounterBasedGauge64 
		MAX-ACCESS read-only 
		STATUS current
		DESCRIPTION  "Status 403 Stats" 
		::={ acosSlbIcapS 41 } 

		status404 OBJECT-TYPE
		SYNTAX  CounterBasedGauge64 
		MAX-ACCESS read-only 
		STATUS current
		DESCRIPTION  "Status 404 Stats" 
		::={ acosSlbIcapS 42 } 

		status405 OBJECT-TYPE
		SYNTAX  CounterBasedGauge64 
		MAX-ACCESS read-only 
		STATUS current
		DESCRIPTION  "Status 405 Stats" 
		::={ acosSlbIcapS 43 } 

		status406 OBJECT-TYPE
		SYNTAX  CounterBasedGauge64 
		MAX-ACCESS read-only 
		STATUS current
		DESCRIPTION  "Status 406 Stats" 
		::={ acosSlbIcapS 44 } 

		status407 OBJECT-TYPE
		SYNTAX  CounterBasedGauge64 
		MAX-ACCESS read-only 
		STATUS current
		DESCRIPTION  "Status 407 Stats" 
		::={ acosSlbIcapS 45 } 

		status408 OBJECT-TYPE
		SYNTAX  CounterBasedGauge64 
		MAX-ACCESS read-only 
		STATUS current
		DESCRIPTION  "Status 408 Stats" 
		::={ acosSlbIcapS 46 } 

		status409 OBJECT-TYPE
		SYNTAX  CounterBasedGauge64 
		MAX-ACCESS read-only 
		STATUS current
		DESCRIPTION  "Status 409 Stats" 
		::={ acosSlbIcapS 47 } 

		status410 OBJECT-TYPE
		SYNTAX  CounterBasedGauge64 
		MAX-ACCESS read-only 
		STATUS current
		DESCRIPTION  "Status 410 Stats" 
		::={ acosSlbIcapS 48 } 

		status411 OBJECT-TYPE
		SYNTAX  CounterBasedGauge64 
		MAX-ACCESS read-only 
		STATUS current
		DESCRIPTION  "Status 411 Stats" 
		::={ acosSlbIcapS 49 } 

		status412 OBJECT-TYPE
		SYNTAX  CounterBasedGauge64 
		MAX-ACCESS read-only 
		STATUS current
		DESCRIPTION  "Status 412 Stats" 
		::={ acosSlbIcapS 50 } 

		status413 OBJECT-TYPE
		SYNTAX  CounterBasedGauge64 
		MAX-ACCESS read-only 
		STATUS current
		DESCRIPTION  "Status 413 Stats" 
		::={ acosSlbIcapS 51 } 

		status414 OBJECT-TYPE
		SYNTAX  CounterBasedGauge64 
		MAX-ACCESS read-only 
		STATUS current
		DESCRIPTION  "Status 414 Stats" 
		::={ acosSlbIcapS 52 } 

		status415 OBJECT-TYPE
		SYNTAX  CounterBasedGauge64 
		MAX-ACCESS read-only 
		STATUS current
		DESCRIPTION  "Status 415 Stats" 
		::={ acosSlbIcapS 53 } 

		status416 OBJECT-TYPE
		SYNTAX  CounterBasedGauge64 
		MAX-ACCESS read-only 
		STATUS current
		DESCRIPTION  "Status 416 Stats" 
		::={ acosSlbIcapS 54 } 

		status417 OBJECT-TYPE
		SYNTAX  CounterBasedGauge64 
		MAX-ACCESS read-only 
		STATUS current
		DESCRIPTION  "Status 417 Stats" 
		::={ acosSlbIcapS 55 } 

		status418 OBJECT-TYPE
		SYNTAX  CounterBasedGauge64 
		MAX-ACCESS read-only 
		STATUS current
		DESCRIPTION  "Status 418 Stats" 
		::={ acosSlbIcapS 56 } 

		status419 OBJECT-TYPE
		SYNTAX  CounterBasedGauge64 
		MAX-ACCESS read-only 
		STATUS current
		DESCRIPTION  "Status 419 Stats" 
		::={ acosSlbIcapS 57 } 

		status420 OBJECT-TYPE
		SYNTAX  CounterBasedGauge64 
		MAX-ACCESS read-only 
		STATUS current
		DESCRIPTION  "Status 420 Stats" 
		::={ acosSlbIcapS 58 } 

		status422 OBJECT-TYPE
		SYNTAX  CounterBasedGauge64 
		MAX-ACCESS read-only 
		STATUS current
		DESCRIPTION  "Status 422 Stats" 
		::={ acosSlbIcapS 59 } 

		status423 OBJECT-TYPE
		SYNTAX  CounterBasedGauge64 
		MAX-ACCESS read-only 
		STATUS current
		DESCRIPTION  "Status 423 Stats" 
		::={ acosSlbIcapS 60 } 

		status424 OBJECT-TYPE
		SYNTAX  CounterBasedGauge64 
		MAX-ACCESS read-only 
		STATUS current
		DESCRIPTION  "Status 424 Stats" 
		::={ acosSlbIcapS 61 } 

		status425 OBJECT-TYPE
		SYNTAX  CounterBasedGauge64 
		MAX-ACCESS read-only 
		STATUS current
		DESCRIPTION  "Status 425 Stats" 
		::={ acosSlbIcapS 62 } 

		status426 OBJECT-TYPE
		SYNTAX  CounterBasedGauge64 
		MAX-ACCESS read-only 
		STATUS current
		DESCRIPTION  "Status 426 Stats" 
		::={ acosSlbIcapS 63 } 

		status449 OBJECT-TYPE
		SYNTAX  CounterBasedGauge64 
		MAX-ACCESS read-only 
		STATUS current
		DESCRIPTION  "Status 449 Stats" 
		::={ acosSlbIcapS 64 } 

		status450 OBJECT-TYPE
		SYNTAX  CounterBasedGauge64 
		MAX-ACCESS read-only 
		STATUS current
		DESCRIPTION  "Status 450 Stats" 
		::={ acosSlbIcapS 65 } 

		status5xx OBJECT-TYPE
		SYNTAX  CounterBasedGauge64 
		MAX-ACCESS read-only 
		STATUS current
		DESCRIPTION  "Status 5xx Stats" 
		::={ acosSlbIcapS 66 } 

		status500 OBJECT-TYPE
		SYNTAX  CounterBasedGauge64 
		MAX-ACCESS read-only 
		STATUS current
		DESCRIPTION  "Status 500 Stats" 
		::={ acosSlbIcapS 67 } 

		status501 OBJECT-TYPE
		SYNTAX  CounterBasedGauge64 
		MAX-ACCESS read-only 
		STATUS current
		DESCRIPTION  "Status 501 Stats" 
		::={ acosSlbIcapS 68 } 

		status502 OBJECT-TYPE
		SYNTAX  CounterBasedGauge64 
		MAX-ACCESS read-only 
		STATUS current
		DESCRIPTION  "Status 502 Stats" 
		::={ acosSlbIcapS 69 } 

		status503 OBJECT-TYPE
		SYNTAX  CounterBasedGauge64 
		MAX-ACCESS read-only 
		STATUS current
		DESCRIPTION  "Status 503 Stats" 
		::={ acosSlbIcapS 70 } 

		status504 OBJECT-TYPE
		SYNTAX  CounterBasedGauge64 
		MAX-ACCESS read-only 
		STATUS current
		DESCRIPTION  "Status 504 Stats" 
		::={ acosSlbIcapS 71 } 

		status505 OBJECT-TYPE
		SYNTAX  CounterBasedGauge64 
		MAX-ACCESS read-only 
		STATUS current
		DESCRIPTION  "Status 505 Stats" 
		::={ acosSlbIcapS 72 } 

		status506 OBJECT-TYPE
		SYNTAX  CounterBasedGauge64 
		MAX-ACCESS read-only 
		STATUS current
		DESCRIPTION  "Status 506 Stats" 
		::={ acosSlbIcapS 73 } 

		status507 OBJECT-TYPE
		SYNTAX  CounterBasedGauge64 
		MAX-ACCESS read-only 
		STATUS current
		DESCRIPTION  "Status 507 Stats" 
		::={ acosSlbIcapS 74 } 

		status508 OBJECT-TYPE
		SYNTAX  CounterBasedGauge64 
		MAX-ACCESS read-only 
		STATUS current
		DESCRIPTION  "Status 508 Stats" 
		::={ acosSlbIcapS 75 } 

		status509 OBJECT-TYPE
		SYNTAX  CounterBasedGauge64 
		MAX-ACCESS read-only 
		STATUS current
		DESCRIPTION  "Status 509 Stats" 
		::={ acosSlbIcapS 76 } 

		status510 OBJECT-TYPE
		SYNTAX  CounterBasedGauge64 
		MAX-ACCESS read-only 
		STATUS current
		DESCRIPTION  "Status 510 Stats" 
		::={ acosSlbIcapS 77 } 

		status6xx OBJECT-TYPE
		SYNTAX  CounterBasedGauge64 
		MAX-ACCESS read-only 
		STATUS current
		DESCRIPTION  "Status 6xx Stats" 
		::={ acosSlbIcapS 78 } 

		statusUnknown OBJECT-TYPE
		SYNTAX  CounterBasedGauge64 
		MAX-ACCESS read-only 
		STATUS current
		DESCRIPTION  "Status Unknown Stats" 
		::={ acosSlbIcapS 79 } 

		sendOptionReq OBJECT-TYPE
		SYNTAX  CounterBasedGauge64 
		MAX-ACCESS read-only 
		STATUS current
		DESCRIPTION  "Send Option Req Stats" 
		::={ acosSlbIcapS 80 } 

		appServConnNoPcbErr OBJECT-TYPE
		SYNTAX  CounterBasedGauge64 
		MAX-ACCESS read-only 
		STATUS current
		DESCRIPTION  "App Server Conn no ES PCB Err Stats" 
		::={ acosSlbIcapS 81 } 

		appServConnErr OBJECT-TYPE
		SYNTAX  CounterBasedGauge64 
		MAX-ACCESS read-only 
		STATUS current
		DESCRIPTION  "App Server Conn Err Stats" 
		::={ acosSlbIcapS 82 } 

		chunk1HdrErr OBJECT-TYPE
		SYNTAX  CounterBasedGauge64 
		MAX-ACCESS read-only 
		STATUS current
		DESCRIPTION  "Chunk Hdr Err1 Stats" 
		::={ acosSlbIcapS 83 } 

		chunk2HdrErr OBJECT-TYPE
		SYNTAX  CounterBasedGauge64 
		MAX-ACCESS read-only 
		STATUS current
		DESCRIPTION  "Chunk Hdr Err2 Stats" 
		::={ acosSlbIcapS 84 } 

		chunkBadTrailErr OBJECT-TYPE
		SYNTAX  CounterBasedGauge64 
		MAX-ACCESS read-only 
		STATUS current
		DESCRIPTION  "Chunk Bad Trail Err Stats" 
		::={ acosSlbIcapS 85 } 

		noPayloadNextBuffErr OBJECT-TYPE
		SYNTAX  CounterBasedGauge64 
		MAX-ACCESS read-only 
		STATUS current
		DESCRIPTION  "No Payload In Next Buff Err Stats" 
		::={ acosSlbIcapS 86 } 

		noPayloadBuffErr OBJECT-TYPE
		SYNTAX  CounterBasedGauge64 
		MAX-ACCESS read-only 
		STATUS current
		DESCRIPTION  "No Payload Buff Err Stats" 
		::={ acosSlbIcapS 87 } 

		respHdrIncompleteErr OBJECT-TYPE
		SYNTAX  CounterBasedGauge64 
		MAX-ACCESS read-only 
		STATUS current
		DESCRIPTION  "Resp Hdr Incomplete Err Stats" 
		::={ acosSlbIcapS 88 } 

		servSelFailErr OBJECT-TYPE
		SYNTAX  CounterBasedGauge64 
		MAX-ACCESS read-only 
		STATUS current
		DESCRIPTION  "Server Select Fail Err Stats" 
		::={ acosSlbIcapS 89 } 

		startIcapConnFailErr OBJECT-TYPE
		SYNTAX  CounterBasedGauge64 
		MAX-ACCESS read-only 
		STATUS current
		DESCRIPTION  "Start ICAP conn fail Stats" 
		::={ acosSlbIcapS 90 } 

		prepReqFailErr OBJECT-TYPE
		SYNTAX  CounterBasedGauge64 
		MAX-ACCESS read-only 
		STATUS current
		DESCRIPTION  "Prepare ICAP req fail Err Stats" 
		::={ acosSlbIcapS 91 } 

		icapVerErr OBJECT-TYPE
		SYNTAX  CounterBasedGauge64 
		MAX-ACCESS read-only 
		STATUS current
		DESCRIPTION  "ICAP Ver Err Stats" 
		::={ acosSlbIcapS 92 } 

		icapLineErr OBJECT-TYPE
		SYNTAX  CounterBasedGauge64 
		MAX-ACCESS read-only 
		STATUS current
		DESCRIPTION  "ICAP Line Err Stats" 
		::={ acosSlbIcapS 93 } 

		encapHdrIncompleteErr OBJECT-TYPE
		SYNTAX  CounterBasedGauge64 
		MAX-ACCESS read-only 
		STATUS current
		DESCRIPTION  "Encap HDR Incomplete Err Stats" 
		::={ acosSlbIcapS 94 } 

		noIcapRespErr OBJECT-TYPE
		SYNTAX  CounterBasedGauge64 
		MAX-ACCESS read-only 
		STATUS current
		DESCRIPTION  "No ICAP Resp Err Stats" 
		::={ acosSlbIcapS 95 } 

		respLineReadErr OBJECT-TYPE
		SYNTAX  CounterBasedGauge64 
		MAX-ACCESS read-only 
		STATUS current
		DESCRIPTION  "Resp Line Read Err Stats" 
		::={ acosSlbIcapS 96 } 

		respLineParseErr OBJECT-TYPE
		SYNTAX  CounterBasedGauge64 
		MAX-ACCESS read-only 
		STATUS current
		DESCRIPTION  "Resp Line Parse Err Stats" 
		::={ acosSlbIcapS 97 } 

		respHdrErr OBJECT-TYPE
		SYNTAX  CounterBasedGauge64 
		MAX-ACCESS read-only 
		STATUS current
		DESCRIPTION  "Resp Hdr Err Stats" 
		::={ acosSlbIcapS 98 } 

		reqHdrIncompleteErr OBJECT-TYPE
		SYNTAX  CounterBasedGauge64 
		MAX-ACCESS read-only 
		STATUS current
		DESCRIPTION  "Req Hdr Incomplete Err Stats" 
		::={ acosSlbIcapS 99 } 

		noStatusCodeErr OBJECT-TYPE
		SYNTAX  CounterBasedGauge64 
		MAX-ACCESS read-only 
		STATUS current
		DESCRIPTION  "No Status Code Err Stats" 
		::={ acosSlbIcapS 100 } 

		httpRespLineReadErr OBJECT-TYPE
		SYNTAX  CounterBasedGauge64 
		MAX-ACCESS read-only 
		STATUS current
		DESCRIPTION  "HTTP Response Line Read Err Stats" 
		::={ acosSlbIcapS 101 } 

		httpRespLineParseErr OBJECT-TYPE
		SYNTAX  CounterBasedGauge64 
		MAX-ACCESS read-only 
		STATUS current
		DESCRIPTION  "HTTP Response Line Parse Err Stats" 
		::={ acosSlbIcapS 102 } 

		httpRespHdrErr OBJECT-TYPE
		SYNTAX  CounterBasedGauge64 
		MAX-ACCESS read-only 
		STATUS current
		DESCRIPTION  "HTTP Resp Hdr Err Stats" 
		::={ acosSlbIcapS 103 } 

		recvOptionResp OBJECT-TYPE
		SYNTAX  CounterBasedGauge64 
		MAX-ACCESS read-only 
		STATUS current
		DESCRIPTION  "Send Option Req Stats" 
		::={ acosSlbIcapS 104 } 

		httpConnectReqmodRequest OBJECT-TYPE
		SYNTAX  CounterBasedGauge64 
		MAX-ACCESS read-only 
		STATUS current
		DESCRIPTION  "HTTP CONNECT Reqmod Request Stats" 
		::={ acosSlbIcapS 105 } 

acosSlbIcapHttp                     OBJECT IDENTIFIER ::= { acosSlb 32 }
acosSlbIcapHttpS                    OBJECT IDENTIFIER ::= { acosSlbIcapHttp 1 }

		status200 OBJECT-TYPE
		SYNTAX  CounterBasedGauge64 
		MAX-ACCESS read-only 
		STATUS current
		DESCRIPTION  "Status code 200" 
		::={ acosSlbIcapHttpS 1 } 

		status201 OBJECT-TYPE
		SYNTAX  CounterBasedGauge64 
		MAX-ACCESS read-only 
		STATUS current
		DESCRIPTION  "Status code 201" 
		::={ acosSlbIcapHttpS 2 } 

		status202 OBJECT-TYPE
		SYNTAX  CounterBasedGauge64 
		MAX-ACCESS read-only 
		STATUS current
		DESCRIPTION  "Status code 202" 
		::={ acosSlbIcapHttpS 3 } 

		status203 OBJECT-TYPE
		SYNTAX  CounterBasedGauge64 
		MAX-ACCESS read-only 
		STATUS current
		DESCRIPTION  "Status code 203" 
		::={ acosSlbIcapHttpS 4 } 

		status204 OBJECT-TYPE
		SYNTAX  CounterBasedGauge64 
		MAX-ACCESS read-only 
		STATUS current
		DESCRIPTION  "Status code 204" 
		::={ acosSlbIcapHttpS 5 } 

		status205 OBJECT-TYPE
		SYNTAX  CounterBasedGauge64 
		MAX-ACCESS read-only 
		STATUS current
		DESCRIPTION  "Status code 205" 
		::={ acosSlbIcapHttpS 6 } 

		status206 OBJECT-TYPE
		SYNTAX  CounterBasedGauge64 
		MAX-ACCESS read-only 
		STATUS current
		DESCRIPTION  "Status code 206" 
		::={ acosSlbIcapHttpS 7 } 

		status207 OBJECT-TYPE
		SYNTAX  CounterBasedGauge64 
		MAX-ACCESS read-only 
		STATUS current
		DESCRIPTION  "Status code 207" 
		::={ acosSlbIcapHttpS 8 } 

		status100 OBJECT-TYPE
		SYNTAX  CounterBasedGauge64 
		MAX-ACCESS read-only 
		STATUS current
		DESCRIPTION  "Status code 100" 
		::={ acosSlbIcapHttpS 9 } 

		status101 OBJECT-TYPE
		SYNTAX  CounterBasedGauge64 
		MAX-ACCESS read-only 
		STATUS current
		DESCRIPTION  "Status code 101" 
		::={ acosSlbIcapHttpS 10 } 

		status102 OBJECT-TYPE
		SYNTAX  CounterBasedGauge64 
		MAX-ACCESS read-only 
		STATUS current
		DESCRIPTION  "Status code 102" 
		::={ acosSlbIcapHttpS 11 } 

		status300 OBJECT-TYPE
		SYNTAX  CounterBasedGauge64 
		MAX-ACCESS read-only 
		STATUS current
		DESCRIPTION  "Status code 300" 
		::={ acosSlbIcapHttpS 12 } 

		status301 OBJECT-TYPE
		SYNTAX  CounterBasedGauge64 
		MAX-ACCESS read-only 
		STATUS current
		DESCRIPTION  "Status code 301" 
		::={ acosSlbIcapHttpS 13 } 

		status302 OBJECT-TYPE
		SYNTAX  CounterBasedGauge64 
		MAX-ACCESS read-only 
		STATUS current
		DESCRIPTION  "Status code 302" 
		::={ acosSlbIcapHttpS 14 } 

		status303 OBJECT-TYPE
		SYNTAX  CounterBasedGauge64 
		MAX-ACCESS read-only 
		STATUS current
		DESCRIPTION  "Status code 303" 
		::={ acosSlbIcapHttpS 15 } 

		status304 OBJECT-TYPE
		SYNTAX  CounterBasedGauge64 
		MAX-ACCESS read-only 
		STATUS current
		DESCRIPTION  "Status code 304" 
		::={ acosSlbIcapHttpS 16 } 

		status305 OBJECT-TYPE
		SYNTAX  CounterBasedGauge64 
		MAX-ACCESS read-only 
		STATUS current
		DESCRIPTION  "Status code 305" 
		::={ acosSlbIcapHttpS 17 } 

		status306 OBJECT-TYPE
		SYNTAX  CounterBasedGauge64 
		MAX-ACCESS read-only 
		STATUS current
		DESCRIPTION  "Status code 306" 
		::={ acosSlbIcapHttpS 18 } 

		status307 OBJECT-TYPE
		SYNTAX  CounterBasedGauge64 
		MAX-ACCESS read-only 
		STATUS current
		DESCRIPTION  "Status code 307" 
		::={ acosSlbIcapHttpS 19 } 

		status400 OBJECT-TYPE
		SYNTAX  CounterBasedGauge64 
		MAX-ACCESS read-only 
		STATUS current
		DESCRIPTION  "Status code 400" 
		::={ acosSlbIcapHttpS 20 } 

		status401 OBJECT-TYPE
		SYNTAX  CounterBasedGauge64 
		MAX-ACCESS read-only 
		STATUS current
		DESCRIPTION  "Status code 401" 
		::={ acosSlbIcapHttpS 21 } 

		status402 OBJECT-TYPE
		SYNTAX  CounterBasedGauge64 
		MAX-ACCESS read-only 
		STATUS current
		DESCRIPTION  "Status code 402" 
		::={ acosSlbIcapHttpS 22 } 

		status403 OBJECT-TYPE
		SYNTAX  CounterBasedGauge64 
		MAX-ACCESS read-only 
		STATUS current
		DESCRIPTION  "Status code 403" 
		::={ acosSlbIcapHttpS 23 } 

		status404 OBJECT-TYPE
		SYNTAX  CounterBasedGauge64 
		MAX-ACCESS read-only 
		STATUS current
		DESCRIPTION  "Status code 404" 
		::={ acosSlbIcapHttpS 24 } 

		status405 OBJECT-TYPE
		SYNTAX  CounterBasedGauge64 
		MAX-ACCESS read-only 
		STATUS current
		DESCRIPTION  "Status code 405" 
		::={ acosSlbIcapHttpS 25 } 

		status406 OBJECT-TYPE
		SYNTAX  CounterBasedGauge64 
		MAX-ACCESS read-only 
		STATUS current
		DESCRIPTION  "Status code 406" 
		::={ acosSlbIcapHttpS 26 } 

		status407 OBJECT-TYPE
		SYNTAX  CounterBasedGauge64 
		MAX-ACCESS read-only 
		STATUS current
		DESCRIPTION  "Status code 407" 
		::={ acosSlbIcapHttpS 27 } 

		status408 OBJECT-TYPE
		SYNTAX  CounterBasedGauge64 
		MAX-ACCESS read-only 
		STATUS current
		DESCRIPTION  "Status code 408" 
		::={ acosSlbIcapHttpS 28 } 

		status409 OBJECT-TYPE
		SYNTAX  CounterBasedGauge64 
		MAX-ACCESS read-only 
		STATUS current
		DESCRIPTION  "Status code 409" 
		::={ acosSlbIcapHttpS 29 } 

		status410 OBJECT-TYPE
		SYNTAX  CounterBasedGauge64 
		MAX-ACCESS read-only 
		STATUS current
		DESCRIPTION  "Status code 410" 
		::={ acosSlbIcapHttpS 30 } 

		status411 OBJECT-TYPE
		SYNTAX  CounterBasedGauge64 
		MAX-ACCESS read-only 
		STATUS current
		DESCRIPTION  "Status code 411" 
		::={ acosSlbIcapHttpS 31 } 

		status412 OBJECT-TYPE
		SYNTAX  CounterBasedGauge64 
		MAX-ACCESS read-only 
		STATUS current
		DESCRIPTION  "Status code 412" 
		::={ acosSlbIcapHttpS 32 } 

		status413 OBJECT-TYPE
		SYNTAX  CounterBasedGauge64 
		MAX-ACCESS read-only 
		STATUS current
		DESCRIPTION  "Status code 413" 
		::={ acosSlbIcapHttpS 33 } 

		status414 OBJECT-TYPE
		SYNTAX  CounterBasedGauge64 
		MAX-ACCESS read-only 
		STATUS current
		DESCRIPTION  "Status code 414" 
		::={ acosSlbIcapHttpS 34 } 

		status415 OBJECT-TYPE
		SYNTAX  CounterBasedGauge64 
		MAX-ACCESS read-only 
		STATUS current
		DESCRIPTION  "Status code 415" 
		::={ acosSlbIcapHttpS 35 } 

		status416 OBJECT-TYPE
		SYNTAX  CounterBasedGauge64 
		MAX-ACCESS read-only 
		STATUS current
		DESCRIPTION  "Status code 416" 
		::={ acosSlbIcapHttpS 36 } 

		status417 OBJECT-TYPE
		SYNTAX  CounterBasedGauge64 
		MAX-ACCESS read-only 
		STATUS current
		DESCRIPTION  "Status code 417" 
		::={ acosSlbIcapHttpS 37 } 

		status418 OBJECT-TYPE
		SYNTAX  CounterBasedGauge64 
		MAX-ACCESS read-only 
		STATUS current
		DESCRIPTION  "Status code 418" 
		::={ acosSlbIcapHttpS 38 } 

		status422 OBJECT-TYPE
		SYNTAX  CounterBasedGauge64 
		MAX-ACCESS read-only 
		STATUS current
		DESCRIPTION  "Status code 422" 
		::={ acosSlbIcapHttpS 39 } 

		status423 OBJECT-TYPE
		SYNTAX  CounterBasedGauge64 
		MAX-ACCESS read-only 
		STATUS current
		DESCRIPTION  "Status code 423" 
		::={ acosSlbIcapHttpS 40 } 

		status424 OBJECT-TYPE
		SYNTAX  CounterBasedGauge64 
		MAX-ACCESS read-only 
		STATUS current
		DESCRIPTION  "Status code 424" 
		::={ acosSlbIcapHttpS 41 } 

		status425 OBJECT-TYPE
		SYNTAX  CounterBasedGauge64 
		MAX-ACCESS read-only 
		STATUS current
		DESCRIPTION  "Status code 425" 
		::={ acosSlbIcapHttpS 42 } 

		status426 OBJECT-TYPE
		SYNTAX  CounterBasedGauge64 
		MAX-ACCESS read-only 
		STATUS current
		DESCRIPTION  "Status code 426" 
		::={ acosSlbIcapHttpS 43 } 

		status449 OBJECT-TYPE
		SYNTAX  CounterBasedGauge64 
		MAX-ACCESS read-only 
		STATUS current
		DESCRIPTION  "Status code 449" 
		::={ acosSlbIcapHttpS 44 } 

		status450 OBJECT-TYPE
		SYNTAX  CounterBasedGauge64 
		MAX-ACCESS read-only 
		STATUS current
		DESCRIPTION  "Status code 450" 
		::={ acosSlbIcapHttpS 45 } 

		status500 OBJECT-TYPE
		SYNTAX  CounterBasedGauge64 
		MAX-ACCESS read-only 
		STATUS current
		DESCRIPTION  "Status code 500" 
		::={ acosSlbIcapHttpS 46 } 

		status501 OBJECT-TYPE
		SYNTAX  CounterBasedGauge64 
		MAX-ACCESS read-only 
		STATUS current
		DESCRIPTION  "Status code 501" 
		::={ acosSlbIcapHttpS 47 } 

		status502 OBJECT-TYPE
		SYNTAX  CounterBasedGauge64 
		MAX-ACCESS read-only 
		STATUS current
		DESCRIPTION  "Status code 502" 
		::={ acosSlbIcapHttpS 48 } 

		status503 OBJECT-TYPE
		SYNTAX  CounterBasedGauge64 
		MAX-ACCESS read-only 
		STATUS current
		DESCRIPTION  "Status code 503" 
		::={ acosSlbIcapHttpS 49 } 

		status504 OBJECT-TYPE
		SYNTAX  CounterBasedGauge64 
		MAX-ACCESS read-only 
		STATUS current
		DESCRIPTION  "Status code 504" 
		::={ acosSlbIcapHttpS 50 } 

		status505 OBJECT-TYPE
		SYNTAX  CounterBasedGauge64 
		MAX-ACCESS read-only 
		STATUS current
		DESCRIPTION  "Status code 505" 
		::={ acosSlbIcapHttpS 51 } 

		status506 OBJECT-TYPE
		SYNTAX  CounterBasedGauge64 
		MAX-ACCESS read-only 
		STATUS current
		DESCRIPTION  "Status code 506" 
		::={ acosSlbIcapHttpS 52 } 

		status507 OBJECT-TYPE
		SYNTAX  CounterBasedGauge64 
		MAX-ACCESS read-only 
		STATUS current
		DESCRIPTION  "Status code 507" 
		::={ acosSlbIcapHttpS 53 } 

		status508 OBJECT-TYPE
		SYNTAX  CounterBasedGauge64 
		MAX-ACCESS read-only 
		STATUS current
		DESCRIPTION  "Status code 508" 
		::={ acosSlbIcapHttpS 54 } 

		status509 OBJECT-TYPE
		SYNTAX  CounterBasedGauge64 
		MAX-ACCESS read-only 
		STATUS current
		DESCRIPTION  "Status code 509" 
		::={ acosSlbIcapHttpS 55 } 

		status510 OBJECT-TYPE
		SYNTAX  CounterBasedGauge64 
		MAX-ACCESS read-only 
		STATUS current
		DESCRIPTION  "Status code 510" 
		::={ acosSlbIcapHttpS 56 } 

		status1xx OBJECT-TYPE
		SYNTAX  CounterBasedGauge64 
		MAX-ACCESS read-only 
		STATUS current
		DESCRIPTION  "status code 1XX" 
		::={ acosSlbIcapHttpS 57 } 

		status2xx OBJECT-TYPE
		SYNTAX  CounterBasedGauge64 
		MAX-ACCESS read-only 
		STATUS current
		DESCRIPTION  "status code 2XX" 
		::={ acosSlbIcapHttpS 58 } 

		status3xx OBJECT-TYPE
		SYNTAX  CounterBasedGauge64 
		MAX-ACCESS read-only 
		STATUS current
		DESCRIPTION  "status code 3XX" 
		::={ acosSlbIcapHttpS 59 } 

		status4xx OBJECT-TYPE
		SYNTAX  CounterBasedGauge64 
		MAX-ACCESS read-only 
		STATUS current
		DESCRIPTION  "status code 4XX" 
		::={ acosSlbIcapHttpS 60 } 

		status5xx OBJECT-TYPE
		SYNTAX  CounterBasedGauge64 
		MAX-ACCESS read-only 
		STATUS current
		DESCRIPTION  "status code 5XX" 
		::={ acosSlbIcapHttpS 61 } 

		status6xx OBJECT-TYPE
		SYNTAX  CounterBasedGauge64 
		MAX-ACCESS read-only 
		STATUS current
		DESCRIPTION  "status code 6XX" 
		::={ acosSlbIcapHttpS 62 } 

		statusUnknown OBJECT-TYPE
		SYNTAX  CounterBasedGauge64 
		MAX-ACCESS read-only 
		STATUS current
		DESCRIPTION  "Status code unknown" 
		::={ acosSlbIcapHttpS 63 } 

acosSlbSip                          OBJECT IDENTIFIER ::= { acosSlb 33 }
acosSlbSipS                         OBJECT IDENTIFIER ::= { acosSlbSip 1 }

		slbSipMsgProxyCurrent OBJECT-TYPE
		SYNTAX  CounterBasedGauge64 
		MAX-ACCESS read-only 
		STATUS current
		DESCRIPTION  "Number of current sip proxy connections" 
		::={ acosSlbSipS 1 } 

		slbSipMsgProxyTotal OBJECT-TYPE
		SYNTAX  CounterBasedGauge64 
		MAX-ACCESS read-only 
		STATUS current
		DESCRIPTION  "Total number of sip proxy connections" 
		::={ acosSlbSipS 2 } 

		msgProxyMemAllocd OBJECT-TYPE
		SYNTAX  CounterBasedGauge64 
		MAX-ACCESS read-only 
		STATUS current
		DESCRIPTION  "" 
		::={ acosSlbSipS 3 } 

		msgProxyMemCached OBJECT-TYPE
		SYNTAX  CounterBasedGauge64 
		MAX-ACCESS read-only 
		STATUS current
		DESCRIPTION  "" 
		::={ acosSlbSipS 4 } 

		msgProxyMemFreed OBJECT-TYPE
		SYNTAX  CounterBasedGauge64 
		MAX-ACCESS read-only 
		STATUS current
		DESCRIPTION  "" 
		::={ acosSlbSipS 5 } 

		slbSipMsgProxyClientRecv OBJECT-TYPE
		SYNTAX  CounterBasedGauge64 
		MAX-ACCESS read-only 
		STATUS current
		DESCRIPTION  "Number of SIP messages received from client" 
		::={ acosSlbSipS 6 } 

		slbSipMsgProxyClientSendSuccess OBJECT-TYPE
		SYNTAX  CounterBasedGauge64 
		MAX-ACCESS read-only 
		STATUS current
		DESCRIPTION  "Number of SIP messages received from client and forwarded to server" 
		::={ acosSlbSipS 7 } 

		slbSipMsgProxyClientIncomplete OBJECT-TYPE
		SYNTAX  CounterBasedGauge64 
		MAX-ACCESS read-only 
		STATUS current
		DESCRIPTION  "Number of packet which contains incomplete message" 
		::={ acosSlbSipS 8 } 

		slbSipMsgProxyClientDrop OBJECT-TYPE
		SYNTAX  CounterBasedGauge64 
		MAX-ACCESS read-only 
		STATUS current
		DESCRIPTION  "Number of AX drop" 
		::={ acosSlbSipS 9 } 

		slbSipMsgProxyClientConnection OBJECT-TYPE
		SYNTAX  CounterBasedGauge64 
		MAX-ACCESS read-only 
		STATUS current
		DESCRIPTION  "Connecting server" 
		::={ acosSlbSipS 10 } 

		slbSipMsgProxyClientFail OBJECT-TYPE
		SYNTAX  CounterBasedGauge64 
		MAX-ACCESS read-only 
		STATUS current
		DESCRIPTION  "Number of SIP messages received from client but failed to forward to server" 
		::={ acosSlbSipS 11 } 

		msgProxyClientFailParse OBJECT-TYPE
		SYNTAX  CounterBasedGauge64 
		MAX-ACCESS read-only 
		STATUS current
		DESCRIPTION  "" 
		::={ acosSlbSipS 12 } 

		msgProxyClientFailProcess OBJECT-TYPE
		SYNTAX  CounterBasedGauge64 
		MAX-ACCESS read-only 
		STATUS current
		DESCRIPTION  "" 
		::={ acosSlbSipS 13 } 

		msgProxyClientFailSnat OBJECT-TYPE
		SYNTAX  CounterBasedGauge64 
		MAX-ACCESS read-only 
		STATUS current
		DESCRIPTION  "" 
		::={ acosSlbSipS 14 } 

		msgProxyClientExceedTmpBuff OBJECT-TYPE
		SYNTAX  CounterBasedGauge64 
		MAX-ACCESS read-only 
		STATUS current
		DESCRIPTION  "" 
		::={ acosSlbSipS 15 } 

		msgProxyClientFailSendPkt OBJECT-TYPE
		SYNTAX  CounterBasedGauge64 
		MAX-ACCESS read-only 
		STATUS current
		DESCRIPTION  "" 
		::={ acosSlbSipS 16 } 

		msgProxyClientFailStartServerConn OBJECT-TYPE
		SYNTAX  CounterBasedGauge64 
		MAX-ACCESS read-only 
		STATUS current
		DESCRIPTION  "" 
		::={ acosSlbSipS 17 } 

		slbSipMsgProxyServerRecv OBJECT-TYPE
		SYNTAX  CounterBasedGauge64 
		MAX-ACCESS read-only 
		STATUS current
		DESCRIPTION  "Number of SIP messages received from server" 
		::={ acosSlbSipS 18 } 

		slbSipMsgProxyServerSendSuccess OBJECT-TYPE
		SYNTAX  CounterBasedGauge64 
		MAX-ACCESS read-only 
		STATUS current
		DESCRIPTION  "Number of SIP messages received from server and forwarded to client" 
		::={ acosSlbSipS 19 } 

		slbSipMsgProxyServerIncomplete OBJECT-TYPE
		SYNTAX  CounterBasedGauge64 
		MAX-ACCESS read-only 
		STATUS current
		DESCRIPTION  "Number of packet which contains incomplete message" 
		::={ acosSlbSipS 20 } 

		slbSipMsgProxyServerDrop OBJECT-TYPE
		SYNTAX  CounterBasedGauge64 
		MAX-ACCESS read-only 
		STATUS current
		DESCRIPTION  "Number of AX drop" 
		::={ acosSlbSipS 21 } 

		slbSipMsgProxyServerFail OBJECT-TYPE
		SYNTAX  CounterBasedGauge64 
		MAX-ACCESS read-only 
		STATUS current
		DESCRIPTION  "Number of SIP messages received from server but failed to forward to client" 
		::={ acosSlbSipS 22 } 

		msgProxyServerFailParse OBJECT-TYPE
		SYNTAX  CounterBasedGauge64 
		MAX-ACCESS read-only 
		STATUS current
		DESCRIPTION  "" 
		::={ acosSlbSipS 23 } 

		msgProxyServerFailProcess OBJECT-TYPE
		SYNTAX  CounterBasedGauge64 
		MAX-ACCESS read-only 
		STATUS current
		DESCRIPTION  "" 
		::={ acosSlbSipS 24 } 

		msgProxyServerFailSelecConnt OBJECT-TYPE
		SYNTAX  CounterBasedGauge64 
		MAX-ACCESS read-only 
		STATUS current
		DESCRIPTION  "" 
		::={ acosSlbSipS 25 } 

		msgProxyServerFailSnat OBJECT-TYPE
		SYNTAX  CounterBasedGauge64 
		MAX-ACCESS read-only 
		STATUS current
		DESCRIPTION  "" 
		::={ acosSlbSipS 26 } 

		msgProxyServerExceedTmpBuff OBJECT-TYPE
		SYNTAX  CounterBasedGauge64 
		MAX-ACCESS read-only 
		STATUS current
		DESCRIPTION  "" 
		::={ acosSlbSipS 27 } 

		msgProxyServerFailSendPkt OBJECT-TYPE
		SYNTAX  CounterBasedGauge64 
		MAX-ACCESS read-only 
		STATUS current
		DESCRIPTION  "" 
		::={ acosSlbSipS 28 } 

		slbSipMsgProxyCreateServerConn OBJECT-TYPE
		SYNTAX  CounterBasedGauge64 
		MAX-ACCESS read-only 
		STATUS current
		DESCRIPTION  "Number of server connection system tries to create" 
		::={ acosSlbSipS 29 } 

		slbSipMsgProxyStartServerConn OBJECT-TYPE
		SYNTAX  CounterBasedGauge64 
		MAX-ACCESS read-only 
		STATUS current
		DESCRIPTION  "Number of server connection created successfully" 
		::={ acosSlbSipS 30 } 

		slbSipMsgProxyFailStartServerConn OBJECT-TYPE
		SYNTAX  CounterBasedGauge64 
		MAX-ACCESS read-only 
		STATUS current
		DESCRIPTION  "Number of server connection create failed" 
		::={ acosSlbSipS 31 } 

		msgProxyServerConnFailSnat OBJECT-TYPE
		SYNTAX  CounterBasedGauge64 
		MAX-ACCESS read-only 
		STATUS current
		DESCRIPTION  "" 
		::={ acosSlbSipS 32 } 

		msgProxyFailConstructServerConn OBJECT-TYPE
		SYNTAX  CounterBasedGauge64 
		MAX-ACCESS read-only 
		STATUS current
		DESCRIPTION  "" 
		::={ acosSlbSipS 33 } 

		msgProxyFailReservePconn OBJECT-TYPE
		SYNTAX  CounterBasedGauge64 
		MAX-ACCESS read-only 
		STATUS current
		DESCRIPTION  "" 
		::={ acosSlbSipS 34 } 

		msgProxyStartServerConnFailed OBJECT-TYPE
		SYNTAX  CounterBasedGauge64 
		MAX-ACCESS read-only 
		STATUS current
		DESCRIPTION  "" 
		::={ acosSlbSipS 35 } 

		msgProxyServerConnAlreadyExists OBJECT-TYPE
		SYNTAX  CounterBasedGauge64 
		MAX-ACCESS read-only 
		STATUS current
		DESCRIPTION  "" 
		::={ acosSlbSipS 36 } 

		msgProxyFailInsertServerConn OBJECT-TYPE
		SYNTAX  CounterBasedGauge64 
		MAX-ACCESS read-only 
		STATUS current
		DESCRIPTION  "" 
		::={ acosSlbSipS 37 } 

		msgProxyParseMsgFail OBJECT-TYPE
		SYNTAX  CounterBasedGauge64 
		MAX-ACCESS read-only 
		STATUS current
		DESCRIPTION  "" 
		::={ acosSlbSipS 38 } 

		msgProxyProcessMsgFail OBJECT-TYPE
		SYNTAX  CounterBasedGauge64 
		MAX-ACCESS read-only 
		STATUS current
		DESCRIPTION  "" 
		::={ acosSlbSipS 39 } 

		msgProxyNoVport OBJECT-TYPE
		SYNTAX  CounterBasedGauge64 
		MAX-ACCESS read-only 
		STATUS current
		DESCRIPTION  "" 
		::={ acosSlbSipS 40 } 

		msgProxyFailSelectServer OBJECT-TYPE
		SYNTAX  CounterBasedGauge64 
		MAX-ACCESS read-only 
		STATUS current
		DESCRIPTION  "" 
		::={ acosSlbSipS 41 } 

		msgProxyFailAllocMem OBJECT-TYPE
		SYNTAX  CounterBasedGauge64 
		MAX-ACCESS read-only 
		STATUS current
		DESCRIPTION  "" 
		::={ acosSlbSipS 42 } 

		msgProxyUnexpectedErr OBJECT-TYPE
		SYNTAX  CounterBasedGauge64 
		MAX-ACCESS read-only 
		STATUS current
		DESCRIPTION  "" 
		::={ acosSlbSipS 43 } 

		msgProxyL7CpuFailed OBJECT-TYPE
		SYNTAX  CounterBasedGauge64 
		MAX-ACCESS read-only 
		STATUS current
		DESCRIPTION  "" 
		::={ acosSlbSipS 44 } 

		msgProxyL4ToL7 OBJECT-TYPE
		SYNTAX  CounterBasedGauge64 
		MAX-ACCESS read-only 
		STATUS current
		DESCRIPTION  "" 
		::={ acosSlbSipS 45 } 

		msgProxyL4FromL7 OBJECT-TYPE
		SYNTAX  CounterBasedGauge64 
		MAX-ACCESS read-only 
		STATUS current
		DESCRIPTION  "" 
		::={ acosSlbSipS 46 } 

		msgProxyToL4SendPkt OBJECT-TYPE
		SYNTAX  CounterBasedGauge64 
		MAX-ACCESS read-only 
		STATUS current
		DESCRIPTION  "" 
		::={ acosSlbSipS 47 } 

		msgProxyL4FromL4Send OBJECT-TYPE
		SYNTAX  CounterBasedGauge64 
		MAX-ACCESS read-only 
		STATUS current
		DESCRIPTION  "" 
		::={ acosSlbSipS 48 } 

		msgProxyL7ToL4 OBJECT-TYPE
		SYNTAX  CounterBasedGauge64 
		MAX-ACCESS read-only 
		STATUS current
		DESCRIPTION  "" 
		::={ acosSlbSipS 49 } 

		msgProxyMagBack OBJECT-TYPE
		SYNTAX  CounterBasedGauge64 
		MAX-ACCESS read-only 
		STATUS current
		DESCRIPTION  "" 
		::={ acosSlbSipS 50 } 

		msgProxyFailDcmsg OBJECT-TYPE
		SYNTAX  CounterBasedGauge64 
		MAX-ACCESS read-only 
		STATUS current
		DESCRIPTION  "" 
		::={ acosSlbSipS 51 } 

		msgProxyDeprecatedConn OBJECT-TYPE
		SYNTAX  CounterBasedGauge64 
		MAX-ACCESS read-only 
		STATUS current
		DESCRIPTION  "" 
		::={ acosSlbSipS 52 } 

		msgProxyHoldMsg OBJECT-TYPE
		SYNTAX  CounterBasedGauge64 
		MAX-ACCESS read-only 
		STATUS current
		DESCRIPTION  "" 
		::={ acosSlbSipS 53 } 

		msgProxySplitPkt OBJECT-TYPE
		SYNTAX  CounterBasedGauge64 
		MAX-ACCESS read-only 
		STATUS current
		DESCRIPTION  "" 
		::={ acosSlbSipS 54 } 

		msgProxyPiplineMsg OBJECT-TYPE
		SYNTAX  CounterBasedGauge64 
		MAX-ACCESS read-only 
		STATUS current
		DESCRIPTION  "" 
		::={ acosSlbSipS 55 } 

		msgProxyClientReset OBJECT-TYPE
		SYNTAX  CounterBasedGauge64 
		MAX-ACCESS read-only 
		STATUS current
		DESCRIPTION  "" 
		::={ acosSlbSipS 56 } 

		msgProxyServerReset OBJECT-TYPE
		SYNTAX  CounterBasedGauge64 
		MAX-ACCESS read-only 
		STATUS current
		DESCRIPTION  "" 
		::={ acosSlbSipS 57 } 

		slbSipSessionCreated OBJECT-TYPE
		SYNTAX  CounterBasedGauge64 
		MAX-ACCESS read-only 
		STATUS current
		DESCRIPTION  "SIP Session created" 
		::={ acosSlbSipS 58 } 

		sessionFreed OBJECT-TYPE
		SYNTAX  CounterBasedGauge64 
		MAX-ACCESS read-only 
		STATUS current
		DESCRIPTION  "SIP Session freed" 
		::={ acosSlbSipS 59 } 

		sessionInRml OBJECT-TYPE
		SYNTAX  CounterBasedGauge64 
		MAX-ACCESS read-only 
		STATUS current
		DESCRIPTION  "" 
		::={ acosSlbSipS 60 } 

		sessionInvalid OBJECT-TYPE
		SYNTAX  CounterBasedGauge64 
		MAX-ACCESS read-only 
		STATUS current
		DESCRIPTION  "" 
		::={ acosSlbSipS 61 } 

		connAllocd OBJECT-TYPE
		SYNTAX  CounterBasedGauge64 
		MAX-ACCESS read-only 
		STATUS current
		DESCRIPTION  "" 
		::={ acosSlbSipS 62 } 

		connFreed OBJECT-TYPE
		SYNTAX  CounterBasedGauge64 
		MAX-ACCESS read-only 
		STATUS current
		DESCRIPTION  "" 
		::={ acosSlbSipS 63 } 

		sessionCallidAllocd OBJECT-TYPE
		SYNTAX  CounterBasedGauge64 
		MAX-ACCESS read-only 
		STATUS current
		DESCRIPTION  "" 
		::={ acosSlbSipS 64 } 

		sessionCallidFreed OBJECT-TYPE
		SYNTAX  CounterBasedGauge64 
		MAX-ACCESS read-only 
		STATUS current
		DESCRIPTION  "" 
		::={ acosSlbSipS 65 } 

		lineMemAllocd OBJECT-TYPE
		SYNTAX  CounterBasedGauge64 
		MAX-ACCESS read-only 
		STATUS current
		DESCRIPTION  "" 
		::={ acosSlbSipS 66 } 

		lineMemFreed OBJECT-TYPE
		SYNTAX  CounterBasedGauge64 
		MAX-ACCESS read-only 
		STATUS current
		DESCRIPTION  "" 
		::={ acosSlbSipS 67 } 

		tableMemAllocd OBJECT-TYPE
		SYNTAX  CounterBasedGauge64 
		MAX-ACCESS read-only 
		STATUS current
		DESCRIPTION  "" 
		::={ acosSlbSipS 68 } 

		tableMemFreed OBJECT-TYPE
		SYNTAX  CounterBasedGauge64 
		MAX-ACCESS read-only 
		STATUS current
		DESCRIPTION  "" 
		::={ acosSlbSipS 69 } 

		cmsgNoUriHeader OBJECT-TYPE
		SYNTAX  CounterBasedGauge64 
		MAX-ACCESS read-only 
		STATUS current
		DESCRIPTION  "" 
		::={ acosSlbSipS 70 } 

		cmsgNoUriSession OBJECT-TYPE
		SYNTAX  CounterBasedGauge64 
		MAX-ACCESS read-only 
		STATUS current
		DESCRIPTION  "" 
		::={ acosSlbSipS 71 } 

		sgNoUriHeader OBJECT-TYPE
		SYNTAX  CounterBasedGauge64 
		MAX-ACCESS read-only 
		STATUS current
		DESCRIPTION  "" 
		::={ acosSlbSipS 72 } 

		smsgNoUriSession OBJECT-TYPE
		SYNTAX  CounterBasedGauge64 
		MAX-ACCESS read-only 
		STATUS current
		DESCRIPTION  "" 
		::={ acosSlbSipS 73 } 

		lineTooLong OBJECT-TYPE
		SYNTAX  CounterBasedGauge64 
		MAX-ACCESS read-only 
		STATUS current
		DESCRIPTION  "" 
		::={ acosSlbSipS 74 } 

		failReadStartLine OBJECT-TYPE
		SYNTAX  CounterBasedGauge64 
		MAX-ACCESS read-only 
		STATUS current
		DESCRIPTION  "" 
		::={ acosSlbSipS 75 } 

		failParseStartLine OBJECT-TYPE
		SYNTAX  CounterBasedGauge64 
		MAX-ACCESS read-only 
		STATUS current
		DESCRIPTION  "" 
		::={ acosSlbSipS 76 } 

		invalidStartLine OBJECT-TYPE
		SYNTAX  CounterBasedGauge64 
		MAX-ACCESS read-only 
		STATUS current
		DESCRIPTION  "" 
		::={ acosSlbSipS 77 } 

		requestUnknownVersion OBJECT-TYPE
		SYNTAX  CounterBasedGauge64 
		MAX-ACCESS read-only 
		STATUS current
		DESCRIPTION  "" 
		::={ acosSlbSipS 78 } 

		responseUnknownVersion OBJECT-TYPE
		SYNTAX  CounterBasedGauge64 
		MAX-ACCESS read-only 
		STATUS current
		DESCRIPTION  "" 
		::={ acosSlbSipS 79 } 

		requestUnknown OBJECT-TYPE
		SYNTAX  CounterBasedGauge64 
		MAX-ACCESS read-only 
		STATUS current
		DESCRIPTION  "" 
		::={ acosSlbSipS 80 } 

		failParseHeaders OBJECT-TYPE
		SYNTAX  CounterBasedGauge64 
		MAX-ACCESS read-only 
		STATUS current
		DESCRIPTION  "" 
		::={ acosSlbSipS 81 } 

		tooManyHeaders OBJECT-TYPE
		SYNTAX  CounterBasedGauge64 
		MAX-ACCESS read-only 
		STATUS current
		DESCRIPTION  "" 
		::={ acosSlbSipS 82 } 

		invalidHeader OBJECT-TYPE
		SYNTAX  CounterBasedGauge64 
		MAX-ACCESS read-only 
		STATUS current
		DESCRIPTION  "" 
		::={ acosSlbSipS 83 } 

		headerNameTooLong OBJECT-TYPE
		SYNTAX  CounterBasedGauge64 
		MAX-ACCESS read-only 
		STATUS current
		DESCRIPTION  "" 
		::={ acosSlbSipS 84 } 

		bodyTooBig OBJECT-TYPE
		SYNTAX  CounterBasedGauge64 
		MAX-ACCESS read-only 
		STATUS current
		DESCRIPTION  "" 
		::={ acosSlbSipS 85 } 

		failGetCounter OBJECT-TYPE
		SYNTAX  CounterBasedGauge64 
		MAX-ACCESS read-only 
		STATUS current
		DESCRIPTION  "" 
		::={ acosSlbSipS 86 } 

		msgNoCallId OBJECT-TYPE
		SYNTAX  CounterBasedGauge64 
		MAX-ACCESS read-only 
		STATUS current
		DESCRIPTION  "" 
		::={ acosSlbSipS 87 } 

		identifyDirFailed OBJECT-TYPE
		SYNTAX  CounterBasedGauge64 
		MAX-ACCESS read-only 
		STATUS current
		DESCRIPTION  "" 
		::={ acosSlbSipS 88 } 

		noSipRequest OBJECT-TYPE
		SYNTAX  CounterBasedGauge64 
		MAX-ACCESS read-only 
		STATUS current
		DESCRIPTION  "" 
		::={ acosSlbSipS 89 } 

		deprecatedMsg OBJECT-TYPE
		SYNTAX  CounterBasedGauge64 
		MAX-ACCESS read-only 
		STATUS current
		DESCRIPTION  "" 
		::={ acosSlbSipS 90 } 

		failInsertCallidSession OBJECT-TYPE
		SYNTAX  CounterBasedGauge64 
		MAX-ACCESS read-only 
		STATUS current
		DESCRIPTION  "" 
		::={ acosSlbSipS 91 } 

		failInsertUriSession OBJECT-TYPE
		SYNTAX  CounterBasedGauge64 
		MAX-ACCESS read-only 
		STATUS current
		DESCRIPTION  "" 
		::={ acosSlbSipS 92 } 

		failInsertHeader OBJECT-TYPE
		SYNTAX  CounterBasedGauge64 
		MAX-ACCESS read-only 
		STATUS current
		DESCRIPTION  "" 
		::={ acosSlbSipS 93 } 

		selectServerConn OBJECT-TYPE
		SYNTAX  CounterBasedGauge64 
		MAX-ACCESS read-only 
		STATUS current
		DESCRIPTION  "" 
		::={ acosSlbSipS 94 } 

		selectServerConnByCallid OBJECT-TYPE
		SYNTAX  CounterBasedGauge64 
		MAX-ACCESS read-only 
		STATUS current
		DESCRIPTION  "" 
		::={ acosSlbSipS 95 } 

		selectServerConnByUri OBJECT-TYPE
		SYNTAX  CounterBasedGauge64 
		MAX-ACCESS read-only 
		STATUS current
		DESCRIPTION  "" 
		::={ acosSlbSipS 96 } 

		selectServerConnByRevTuple OBJECT-TYPE
		SYNTAX  CounterBasedGauge64 
		MAX-ACCESS read-only 
		STATUS current
		DESCRIPTION  "" 
		::={ acosSlbSipS 97 } 

		selectServerConnFailed OBJECT-TYPE
		SYNTAX  CounterBasedGauge64 
		MAX-ACCESS read-only 
		STATUS current
		DESCRIPTION  "" 
		::={ acosSlbSipS 98 } 

		selectClientConn OBJECT-TYPE
		SYNTAX  CounterBasedGauge64 
		MAX-ACCESS read-only 
		STATUS current
		DESCRIPTION  "" 
		::={ acosSlbSipS 99 } 

		xForwardedForClient OBJECT-TYPE
		SYNTAX  CounterBasedGauge64 
		MAX-ACCESS read-only 
		STATUS current
		DESCRIPTION  "" 
		::={ acosSlbSipS 100 } 

		callIdSelectClient OBJECT-TYPE
		SYNTAX  CounterBasedGauge64 
		MAX-ACCESS read-only 
		STATUS current
		DESCRIPTION  "" 
		::={ acosSlbSipS 101 } 

		uriSelectClient OBJECT-TYPE
		SYNTAX  CounterBasedGauge64 
		MAX-ACCESS read-only 
		STATUS current
		DESCRIPTION  "" 
		::={ acosSlbSipS 102 } 

		clientSelectFailed OBJECT-TYPE
		SYNTAX  CounterBasedGauge64 
		MAX-ACCESS read-only 
		STATUS current
		DESCRIPTION  "" 
		::={ acosSlbSipS 103 } 

		aclDenied OBJECT-TYPE
		SYNTAX  CounterBasedGauge64 
		MAX-ACCESS read-only 
		STATUS current
		DESCRIPTION  "" 
		::={ acosSlbSipS 104 } 

		assembleFragFailed OBJECT-TYPE
		SYNTAX  CounterBasedGauge64 
		MAX-ACCESS read-only 
		STATUS current
		DESCRIPTION  "" 
		::={ acosSlbSipS 105 } 

		wrongIpVersion OBJECT-TYPE
		SYNTAX  CounterBasedGauge64 
		MAX-ACCESS read-only 
		STATUS current
		DESCRIPTION  "" 
		::={ acosSlbSipS 106 } 

		sizeTooLarge OBJECT-TYPE
		SYNTAX  CounterBasedGauge64 
		MAX-ACCESS read-only 
		STATUS current
		DESCRIPTION  "" 
		::={ acosSlbSipS 107 } 

		failSplitFragment OBJECT-TYPE
		SYNTAX  CounterBasedGauge64 
		MAX-ACCESS read-only 
		STATUS current
		DESCRIPTION  "" 
		::={ acosSlbSipS 108 } 

		clientKeepaliveReceived OBJECT-TYPE
		SYNTAX  CounterBasedGauge64 
		MAX-ACCESS read-only 
		STATUS current
		DESCRIPTION  "" 
		::={ acosSlbSipS 109 } 

		serverKeepaliveReceived OBJECT-TYPE
		SYNTAX  CounterBasedGauge64 
		MAX-ACCESS read-only 
		STATUS current
		DESCRIPTION  "" 
		::={ acosSlbSipS 110 } 

		clientKeepaliveSend OBJECT-TYPE
		SYNTAX  CounterBasedGauge64 
		MAX-ACCESS read-only 
		STATUS current
		DESCRIPTION  "" 
		::={ acosSlbSipS 111 } 

		serverKeepaliveSend OBJECT-TYPE
		SYNTAX  CounterBasedGauge64 
		MAX-ACCESS read-only 
		STATUS current
		DESCRIPTION  "" 
		::={ acosSlbSipS 112 } 

		axHealthCheckReceived OBJECT-TYPE
		SYNTAX  CounterBasedGauge64 
		MAX-ACCESS read-only 
		STATUS current
		DESCRIPTION  "" 
		::={ acosSlbSipS 113 } 

		clientRequest OBJECT-TYPE
		SYNTAX  CounterBasedGauge64 
		MAX-ACCESS read-only 
		STATUS current
		DESCRIPTION  "" 
		::={ acosSlbSipS 114 } 

		clientRequestOk OBJECT-TYPE
		SYNTAX  CounterBasedGauge64 
		MAX-ACCESS read-only 
		STATUS current
		DESCRIPTION  "" 
		::={ acosSlbSipS 115 } 

		concatenateMsg OBJECT-TYPE
		SYNTAX  CounterBasedGauge64 
		MAX-ACCESS read-only 
		STATUS current
		DESCRIPTION  "" 
		::={ acosSlbSipS 116 } 

		saveUri OBJECT-TYPE
		SYNTAX  CounterBasedGauge64 
		MAX-ACCESS read-only 
		STATUS current
		DESCRIPTION  "" 
		::={ acosSlbSipS 117 } 

		saveUriOk OBJECT-TYPE
		SYNTAX  CounterBasedGauge64 
		MAX-ACCESS read-only 
		STATUS current
		DESCRIPTION  "" 
		::={ acosSlbSipS 118 } 

		saveCallId OBJECT-TYPE
		SYNTAX  CounterBasedGauge64 
		MAX-ACCESS read-only 
		STATUS current
		DESCRIPTION  "" 
		::={ acosSlbSipS 119 } 

		saveCallIdOk OBJECT-TYPE
		SYNTAX  CounterBasedGauge64 
		MAX-ACCESS read-only 
		STATUS current
		DESCRIPTION  "" 
		::={ acosSlbSipS 120 } 

		msgTranslation OBJECT-TYPE
		SYNTAX  CounterBasedGauge64 
		MAX-ACCESS read-only 
		STATUS current
		DESCRIPTION  "" 
		::={ acosSlbSipS 121 } 

		msgTranslationFail OBJECT-TYPE
		SYNTAX  CounterBasedGauge64 
		MAX-ACCESS read-only 
		STATUS current
		DESCRIPTION  "" 
		::={ acosSlbSipS 122 } 

		msgTransStartLine OBJECT-TYPE
		SYNTAX  CounterBasedGauge64 
		MAX-ACCESS read-only 
		STATUS current
		DESCRIPTION  "" 
		::={ acosSlbSipS 123 } 

		msgTransStartHeaders OBJECT-TYPE
		SYNTAX  CounterBasedGauge64 
		MAX-ACCESS read-only 
		STATUS current
		DESCRIPTION  "" 
		::={ acosSlbSipS 124 } 

		msgTransBody OBJECT-TYPE
		SYNTAX  CounterBasedGauge64 
		MAX-ACCESS read-only 
		STATUS current
		DESCRIPTION  "" 
		::={ acosSlbSipS 125 } 

		requestRegister OBJECT-TYPE
		SYNTAX  CounterBasedGauge64 
		MAX-ACCESS read-only 
		STATUS current
		DESCRIPTION  "" 
		::={ acosSlbSipS 126 } 

		requestInvite OBJECT-TYPE
		SYNTAX  CounterBasedGauge64 
		MAX-ACCESS read-only 
		STATUS current
		DESCRIPTION  "" 
		::={ acosSlbSipS 127 } 

		requestAck OBJECT-TYPE
		SYNTAX  CounterBasedGauge64 
		MAX-ACCESS read-only 
		STATUS current
		DESCRIPTION  "" 
		::={ acosSlbSipS 128 } 

		requestCancel OBJECT-TYPE
		SYNTAX  CounterBasedGauge64 
		MAX-ACCESS read-only 
		STATUS current
		DESCRIPTION  "" 
		::={ acosSlbSipS 129 } 

		requestBye OBJECT-TYPE
		SYNTAX  CounterBasedGauge64 
		MAX-ACCESS read-only 
		STATUS current
		DESCRIPTION  "" 
		::={ acosSlbSipS 130 } 

		requestOptions OBJECT-TYPE
		SYNTAX  CounterBasedGauge64 
		MAX-ACCESS read-only 
		STATUS current
		DESCRIPTION  "" 
		::={ acosSlbSipS 131 } 

		requestPrack OBJECT-TYPE
		SYNTAX  CounterBasedGauge64 
		MAX-ACCESS read-only 
		STATUS current
		DESCRIPTION  "" 
		::={ acosSlbSipS 132 } 

		requestSubscribe OBJECT-TYPE
		SYNTAX  CounterBasedGauge64 
		MAX-ACCESS read-only 
		STATUS current
		DESCRIPTION  "" 
		::={ acosSlbSipS 133 } 

		requestNotify OBJECT-TYPE
		SYNTAX  CounterBasedGauge64 
		MAX-ACCESS read-only 
		STATUS current
		DESCRIPTION  "" 
		::={ acosSlbSipS 134 } 

		requestPublish OBJECT-TYPE
		SYNTAX  CounterBasedGauge64 
		MAX-ACCESS read-only 
		STATUS current
		DESCRIPTION  "" 
		::={ acosSlbSipS 135 } 

		requestInfo OBJECT-TYPE
		SYNTAX  CounterBasedGauge64 
		MAX-ACCESS read-only 
		STATUS current
		DESCRIPTION  "" 
		::={ acosSlbSipS 136 } 

		requestRefer OBJECT-TYPE
		SYNTAX  CounterBasedGauge64 
		MAX-ACCESS read-only 
		STATUS current
		DESCRIPTION  "" 
		::={ acosSlbSipS 137 } 

		requestMessage OBJECT-TYPE
		SYNTAX  CounterBasedGauge64 
		MAX-ACCESS read-only 
		STATUS current
		DESCRIPTION  "" 
		::={ acosSlbSipS 138 } 

		requestUpdate OBJECT-TYPE
		SYNTAX  CounterBasedGauge64 
		MAX-ACCESS read-only 
		STATUS current
		DESCRIPTION  "" 
		::={ acosSlbSipS 139 } 

		responseUnknown OBJECT-TYPE
		SYNTAX  CounterBasedGauge64 
		MAX-ACCESS read-only 
		STATUS current
		DESCRIPTION  "" 
		::={ acosSlbSipS 140 } 

		response1XX OBJECT-TYPE
		SYNTAX  CounterBasedGauge64 
		MAX-ACCESS read-only 
		STATUS current
		DESCRIPTION  "" 
		::={ acosSlbSipS 141 } 

		response2XX OBJECT-TYPE
		SYNTAX  CounterBasedGauge64 
		MAX-ACCESS read-only 
		STATUS current
		DESCRIPTION  "" 
		::={ acosSlbSipS 142 } 

		response3XX OBJECT-TYPE
		SYNTAX  CounterBasedGauge64 
		MAX-ACCESS read-only 
		STATUS current
		DESCRIPTION  "" 
		::={ acosSlbSipS 143 } 

		response4XX OBJECT-TYPE
		SYNTAX  CounterBasedGauge64 
		MAX-ACCESS read-only 
		STATUS current
		DESCRIPTION  "" 
		::={ acosSlbSipS 144 } 

		response5XX OBJECT-TYPE
		SYNTAX  CounterBasedGauge64 
		MAX-ACCESS read-only 
		STATUS current
		DESCRIPTION  "" 
		::={ acosSlbSipS 145 } 

		response6XX OBJECT-TYPE
		SYNTAX  CounterBasedGauge64 
		MAX-ACCESS read-only 
		STATUS current
		DESCRIPTION  "" 
		::={ acosSlbSipS 146 } 

		haSendSipSession OBJECT-TYPE
		SYNTAX  CounterBasedGauge64 
		MAX-ACCESS read-only 
		STATUS current
		DESCRIPTION  "" 
		::={ acosSlbSipS 147 } 

		haSendSipSessionOk OBJECT-TYPE
		SYNTAX  CounterBasedGauge64 
		MAX-ACCESS read-only 
		STATUS current
		DESCRIPTION  "" 
		::={ acosSlbSipS 148 } 

		haFailGetMsgHeader OBJECT-TYPE
		SYNTAX  CounterBasedGauge64 
		MAX-ACCESS read-only 
		STATUS current
		DESCRIPTION  "" 
		::={ acosSlbSipS 149 } 

		haRecvSipSession OBJECT-TYPE
		SYNTAX  CounterBasedGauge64 
		MAX-ACCESS read-only 
		STATUS current
		DESCRIPTION  "" 
		::={ acosSlbSipS 150 } 

		haInsertSipSessionOk OBJECT-TYPE
		SYNTAX  CounterBasedGauge64 
		MAX-ACCESS read-only 
		STATUS current
		DESCRIPTION  "" 
		::={ acosSlbSipS 151 } 

		haUpdateSipSessionOk OBJECT-TYPE
		SYNTAX  CounterBasedGauge64 
		MAX-ACCESS read-only 
		STATUS current
		DESCRIPTION  "" 
		::={ acosSlbSipS 152 } 

		haInvalidPkt OBJECT-TYPE
		SYNTAX  CounterBasedGauge64 
		MAX-ACCESS read-only 
		STATUS current
		DESCRIPTION  "" 
		::={ acosSlbSipS 153 } 

		haFailAllocSipSession OBJECT-TYPE
		SYNTAX  CounterBasedGauge64 
		MAX-ACCESS read-only 
		STATUS current
		DESCRIPTION  "" 
		::={ acosSlbSipS 154 } 

		haFailAllocCallId OBJECT-TYPE
		SYNTAX  CounterBasedGauge64 
		MAX-ACCESS read-only 
		STATUS current
		DESCRIPTION  "" 
		::={ acosSlbSipS 155 } 

		haFailCloneSipSession OBJECT-TYPE
		SYNTAX  CounterBasedGauge64 
		MAX-ACCESS read-only 
		STATUS current
		DESCRIPTION  "" 
		::={ acosSlbSipS 156 } 

		saveSmpCallIdRtp OBJECT-TYPE
		SYNTAX  CounterBasedGauge64 
		MAX-ACCESS read-only 
		STATUS current
		DESCRIPTION  "" 
		::={ acosSlbSipS 157 } 

		updateSmpCallIdRtp OBJECT-TYPE
		SYNTAX  CounterBasedGauge64 
		MAX-ACCESS read-only 
		STATUS current
		DESCRIPTION  "" 
		::={ acosSlbSipS 158 } 

		smpCallIdRtpSessionMatch OBJECT-TYPE
		SYNTAX  CounterBasedGauge64 
		MAX-ACCESS read-only 
		STATUS current
		DESCRIPTION  "" 
		::={ acosSlbSipS 159 } 

		smpCallIdRtpSessionNotMatch OBJECT-TYPE
		SYNTAX  CounterBasedGauge64 
		MAX-ACCESS read-only 
		STATUS current
		DESCRIPTION  "" 
		::={ acosSlbSipS 160 } 

		processErrorWhenMessageSwitch OBJECT-TYPE
		SYNTAX  CounterBasedGauge64 
		MAX-ACCESS read-only 
		STATUS current
		DESCRIPTION  "" 
		::={ acosSlbSipS 161 } 

acosSlbHwCompress                   OBJECT IDENTIFIER ::= { acosSlb 34 }
acosSlbHwCompressS                  OBJECT IDENTIFIER ::= { acosSlbHwCompress 1 }

		requestCount OBJECT-TYPE
		SYNTAX  CounterBasedGauge64 
		MAX-ACCESS read-only 
		STATUS current
		DESCRIPTION  "Total request count" 
		::={ acosSlbHwCompressS 1 } 

		submitCount OBJECT-TYPE
		SYNTAX  CounterBasedGauge64 
		MAX-ACCESS read-only 
		STATUS current
		DESCRIPTION  "Total submit count" 
		::={ acosSlbHwCompressS 2 } 

		responseCount OBJECT-TYPE
		SYNTAX  CounterBasedGauge64 
		MAX-ACCESS read-only 
		STATUS current
		DESCRIPTION  "Total response count" 
		::={ acosSlbHwCompressS 3 } 

		failureCount OBJECT-TYPE
		SYNTAX  CounterBasedGauge64 
		MAX-ACCESS read-only 
		STATUS current
		DESCRIPTION  "Total failure count" 
		::={ acosSlbHwCompressS 4 } 

		failureCode OBJECT-TYPE
		SYNTAX  CounterBasedGauge64 
		MAX-ACCESS read-only 
		STATUS current
		DESCRIPTION  "Last failure code" 
		::={ acosSlbHwCompressS 5 } 

		ringFullCount OBJECT-TYPE
		SYNTAX  CounterBasedGauge64 
		MAX-ACCESS read-only 
		STATUS current
		DESCRIPTION  "Compression queue full" 
		::={ acosSlbHwCompressS 6 } 

		maxOutstandingRequestCount OBJECT-TYPE
		SYNTAX  CounterBasedGauge64 
		MAX-ACCESS read-only 
		STATUS current
		DESCRIPTION  "Max queued request count" 
		::={ acosSlbHwCompressS 7 } 

		maxOutstandingSubmitCount OBJECT-TYPE
		SYNTAX  CounterBasedGauge64 
		MAX-ACCESS read-only 
		STATUS current
		DESCRIPTION  "Max queued submit count" 
		::={ acosSlbHwCompressS 8 } 

acosSlbDns64                        OBJECT IDENTIFIER ::= { acosSlb 104 }
acosSlbDns64S                       OBJECT IDENTIFIER ::= { acosSlbDns64 1 }

		query OBJECT-TYPE
		SYNTAX  CounterBasedGauge64 
		MAX-ACCESS read-only 
		STATUS current
		DESCRIPTION  "Query" 
		::={ acosSlbDns64S 1 } 

		queryBadPkt OBJECT-TYPE
		SYNTAX  CounterBasedGauge64 
		MAX-ACCESS read-only 
		STATUS current
		DESCRIPTION  "Query Bad Packet" 
		::={ acosSlbDns64S 2 } 

		queryChg OBJECT-TYPE
		SYNTAX  CounterBasedGauge64 
		MAX-ACCESS read-only 
		STATUS current
		DESCRIPTION  "Query Changed" 
		::={ acosSlbDns64S 3 } 

		queryParallel OBJECT-TYPE
		SYNTAX  CounterBasedGauge64 
		MAX-ACCESS read-only 
		STATUS current
		DESCRIPTION  "Query Parallel" 
		::={ acosSlbDns64S 4 } 

		queryPassive OBJECT-TYPE
		SYNTAX  CounterBasedGauge64 
		MAX-ACCESS read-only 
		STATUS current
		DESCRIPTION  "Query Passive" 
		::={ acosSlbDns64S 5 } 

		resp OBJECT-TYPE
		SYNTAX  CounterBasedGauge64 
		MAX-ACCESS read-only 
		STATUS current
		DESCRIPTION  "Response" 
		::={ acosSlbDns64S 6 } 

		respBadPkt OBJECT-TYPE
		SYNTAX  CounterBasedGauge64 
		MAX-ACCESS read-only 
		STATUS current
		DESCRIPTION  "Response Bad Packet" 
		::={ acosSlbDns64S 7 } 

		respBadQr OBJECT-TYPE
		SYNTAX  CounterBasedGauge64 
		MAX-ACCESS read-only 
		STATUS current
		DESCRIPTION  "Response Bad Query" 
		::={ acosSlbDns64S 8 } 

		respChg OBJECT-TYPE
		SYNTAX  CounterBasedGauge64 
		MAX-ACCESS read-only 
		STATUS current
		DESCRIPTION  "Response Changed" 
		::={ acosSlbDns64S 9 } 

		respErr OBJECT-TYPE
		SYNTAX  CounterBasedGauge64 
		MAX-ACCESS read-only 
		STATUS current
		DESCRIPTION  "Response Error" 
		::={ acosSlbDns64S 10 } 

		respEmpty OBJECT-TYPE
		SYNTAX  CounterBasedGauge64 
		MAX-ACCESS read-only 
		STATUS current
		DESCRIPTION  "Response Empty" 
		::={ acosSlbDns64S 11 } 

		respLocal OBJECT-TYPE
		SYNTAX  CounterBasedGauge64 
		MAX-ACCESS read-only 
		STATUS current
		DESCRIPTION  "Response Local" 
		::={ acosSlbDns64S 12 } 

		adjust OBJECT-TYPE
		SYNTAX  CounterBasedGauge64 
		MAX-ACCESS read-only 
		STATUS current
		DESCRIPTION  "Translated" 
		::={ acosSlbDns64S 13 } 

		cache OBJECT-TYPE
		SYNTAX  CounterBasedGauge64 
		MAX-ACCESS read-only 
		STATUS current
		DESCRIPTION  "Cache" 
		::={ acosSlbDns64S 14 } 

		drop OBJECT-TYPE
		SYNTAX  CounterBasedGauge64 
		MAX-ACCESS read-only 
		STATUS current
		DESCRIPTION  "Dropped" 
		::={ acosSlbDns64S 15 } 

acosSlbHealthStat                   OBJECT IDENTIFIER ::= { acosSlb 35 }
acosSlbHealthStatS                  OBJECT IDENTIFIER ::= { acosSlbHealthStat 1 }

		numBurst OBJECT-TYPE
		SYNTAX  CounterBasedGauge64 
		MAX-ACCESS read-only 
		STATUS current
		DESCRIPTION  "Number of burst" 
		::={ acosSlbHealthStatS 1 } 

		maxJiffie OBJECT-TYPE
		SYNTAX  CounterBasedGauge64 
		MAX-ACCESS read-only 
		STATUS current
		DESCRIPTION  "Maximum number of jiffies" 
		::={ acosSlbHealthStatS 2 } 

		minJiffie OBJECT-TYPE
		SYNTAX  CounterBasedGauge64 
		MAX-ACCESS read-only 
		STATUS current
		DESCRIPTION  "Minimum number of jiffies" 
		::={ acosSlbHealthStatS 3 } 

		avgJiffie OBJECT-TYPE
		SYNTAX  CounterBasedGauge64 
		MAX-ACCESS read-only 
		STATUS current
		DESCRIPTION  "Average number of jiffies" 
		::={ acosSlbHealthStatS 4 } 

		openSocket OBJECT-TYPE
		SYNTAX  CounterBasedGauge64 
		MAX-ACCESS read-only 
		STATUS current
		DESCRIPTION  "Number of open sockets" 
		::={ acosSlbHealthStatS 5 } 

		openSocketFailed OBJECT-TYPE
		SYNTAX  CounterBasedGauge64 
		MAX-ACCESS read-only 
		STATUS current
		DESCRIPTION  "Number of failed open sockets" 
		::={ acosSlbHealthStatS 6 } 

		closeSocket OBJECT-TYPE
		SYNTAX  CounterBasedGauge64 
		MAX-ACCESS read-only 
		STATUS current
		DESCRIPTION  "Number of closed sockets" 
		::={ acosSlbHealthStatS 7 } 

		connectFailed OBJECT-TYPE
		SYNTAX  CounterBasedGauge64 
		MAX-ACCESS read-only 
		STATUS current
		DESCRIPTION  "Number of failed connections" 
		::={ acosSlbHealthStatS 8 } 

		sendPacket OBJECT-TYPE
		SYNTAX  CounterBasedGauge64 
		MAX-ACCESS read-only 
		STATUS current
		DESCRIPTION  "Number of packets sent" 
		::={ acosSlbHealthStatS 9 } 

		sendPacketFailed OBJECT-TYPE
		SYNTAX  CounterBasedGauge64 
		MAX-ACCESS read-only 
		STATUS current
		DESCRIPTION  "Number of packet send failures" 
		::={ acosSlbHealthStatS 10 } 

		recvPacket OBJECT-TYPE
		SYNTAX  CounterBasedGauge64 
		MAX-ACCESS read-only 
		STATUS current
		DESCRIPTION  "Number of received packets" 
		::={ acosSlbHealthStatS 11 } 

		recvPacketFailed OBJECT-TYPE
		SYNTAX  CounterBasedGauge64 
		MAX-ACCESS read-only 
		STATUS current
		DESCRIPTION  "Number of failed packet receives" 
		::={ acosSlbHealthStatS 12 } 

		retryTimes OBJECT-TYPE
		SYNTAX  CounterBasedGauge64 
		MAX-ACCESS read-only 
		STATUS current
		DESCRIPTION  "Retry times" 
		::={ acosSlbHealthStatS 13 } 

		timeout OBJECT-TYPE
		SYNTAX  CounterBasedGauge64 
		MAX-ACCESS read-only 
		STATUS current
		DESCRIPTION  "Timouet value" 
		::={ acosSlbHealthStatS 14 } 

		unexpectedError OBJECT-TYPE
		SYNTAX  CounterBasedGauge64 
		MAX-ACCESS read-only 
		STATUS current
		DESCRIPTION  "Number of unexpected errors" 
		::={ acosSlbHealthStatS 15 } 

		connImdtSucc OBJECT-TYPE
		SYNTAX  CounterBasedGauge64 
		MAX-ACCESS read-only 
		STATUS current
		DESCRIPTION  "Number of connection immediete success" 
		::={ acosSlbHealthStatS 16 } 

		sockCloseBefore17 OBJECT-TYPE
		SYNTAX  CounterBasedGauge64 
		MAX-ACCESS read-only 
		STATUS current
		DESCRIPTION  "Number of sockets closed before l7" 
		::={ acosSlbHealthStatS 17 } 

		sockCloseWithoutNotify OBJECT-TYPE
		SYNTAX  CounterBasedGauge64 
		MAX-ACCESS read-only 
		STATUS current
		DESCRIPTION  "Number of sockets closed without notify" 
		::={ acosSlbHealthStatS 18 } 

		currHealthRate OBJECT-TYPE
		SYNTAX  CounterBasedGauge64 
		MAX-ACCESS read-only 
		STATUS current
		DESCRIPTION  "Current health rate" 
		::={ acosSlbHealthStatS 19 } 

		extHealthRate OBJECT-TYPE
		SYNTAX  CounterBasedGauge64 
		MAX-ACCESS read-only 
		STATUS current
		DESCRIPTION  "External health rate" 
		::={ acosSlbHealthStatS 20 } 

		extHealthRateVal OBJECT-TYPE
		SYNTAX  CounterBasedGauge64 
		MAX-ACCESS read-only 
		STATUS current
		DESCRIPTION  "External health rate value" 
		::={ acosSlbHealthStatS 21 } 

		totalNumber OBJECT-TYPE
		SYNTAX  CounterBasedGauge64 
		MAX-ACCESS read-only 
		STATUS current
		DESCRIPTION  "Total number" 
		::={ acosSlbHealthStatS 22 } 

		statusUp OBJECT-TYPE
		SYNTAX  CounterBasedGauge64 
		MAX-ACCESS read-only 
		STATUS current
		DESCRIPTION  "Number of status ups" 
		::={ acosSlbHealthStatS 23 } 

		statusDown OBJECT-TYPE
		SYNTAX  CounterBasedGauge64 
		MAX-ACCESS read-only 
		STATUS current
		DESCRIPTION  "Number of status downs" 
		::={ acosSlbHealthStatS 24 } 

		statusUnkn OBJECT-TYPE
		SYNTAX  CounterBasedGauge64 
		MAX-ACCESS read-only 
		STATUS current
		DESCRIPTION  "Number of status unknowns" 
		::={ acosSlbHealthStatS 25 } 

		statusOther OBJECT-TYPE
		SYNTAX  CounterBasedGauge64 
		MAX-ACCESS read-only 
		STATUS current
		DESCRIPTION  "Number of other status" 
		::={ acosSlbHealthStatS 26 } 

		runningTime OBJECT-TYPE
		SYNTAX  CounterBasedGauge64 
		MAX-ACCESS read-only 
		STATUS current
		DESCRIPTION  "Running time" 
		::={ acosSlbHealthStatS 27 } 

		configHealthRate OBJECT-TYPE
		SYNTAX  CounterBasedGauge64 
		MAX-ACCESS read-only 
		STATUS current
		DESCRIPTION  "Config health rate" 
		::={ acosSlbHealthStatS 28 } 

		sslPostHandshakePacket OBJECT-TYPE
		SYNTAX  CounterBasedGauge64 
		MAX-ACCESS read-only 
		STATUS current
		DESCRIPTION  "Number of ssl post handshake packets before client sends request" 
		::={ acosSlbHealthStatS 29 } 

		timeoutWithPacket OBJECT-TYPE
		SYNTAX  CounterBasedGauge64 
		MAX-ACCESS read-only 
		STATUS current
		DESCRIPTION  "Number of pin timeouts while socket has packets" 
		::={ acosSlbHealthStatS 30 } 

acosSlbHealthGateway                OBJECT IDENTIFIER ::= { acosSlb 36 }
acosSlbHealthGatewayS               OBJECT IDENTIFIER ::= { acosSlbHealthGateway 1 }

		totalSent OBJECT-TYPE
		SYNTAX  CounterBasedGauge64 
		MAX-ACCESS read-only 
		STATUS current
		DESCRIPTION  "Number of Total health-check sent" 
		::={ acosSlbHealthGatewayS 1 } 

		totalRetrySent OBJECT-TYPE
		SYNTAX  CounterBasedGauge64 
		MAX-ACCESS read-only 
		STATUS current
		DESCRIPTION  "Number of Total health-check retry sent" 
		::={ acosSlbHealthGatewayS 2 } 

		totalTimeout OBJECT-TYPE
		SYNTAX  CounterBasedGauge64 
		MAX-ACCESS read-only 
		STATUS current
		DESCRIPTION  "Number of Total health-check timeout" 
		::={ acosSlbHealthGatewayS 3 } 

acosSlbPassthrough                  OBJECT IDENTIFIER ::= { acosSlb 37 }
acosSlbPassthroughS                 OBJECT IDENTIFIER ::= { acosSlbPassthrough 1 }

		slbPassthroughCurrConn OBJECT-TYPE
		SYNTAX  CounterBasedGauge64 
		MAX-ACCESS read-only 
		STATUS current
		DESCRIPTION  "Current connections" 
		::={ acosSlbPassthroughS 1 } 

		slbPassthroughTotalConn OBJECT-TYPE
		SYNTAX  CounterBasedGauge64 
		MAX-ACCESS read-only 
		STATUS current
		DESCRIPTION  "Total connections" 
		::={ acosSlbPassthroughS 2 } 

		slbPassthroughTotalFwdBytes OBJECT-TYPE
		SYNTAX  CounterBasedGauge64 
		MAX-ACCESS read-only 
		STATUS current
		DESCRIPTION  "Forward bytes" 
		::={ acosSlbPassthroughS 3 } 

		slbPassthroughTotalFwdPackets OBJECT-TYPE
		SYNTAX  CounterBasedGauge64 
		MAX-ACCESS read-only 
		STATUS current
		DESCRIPTION  "Forward packets" 
		::={ acosSlbPassthroughS 4 } 

		slbPassthroughTotalRevBytes OBJECT-TYPE
		SYNTAX  CounterBasedGauge64 
		MAX-ACCESS read-only 
		STATUS current
		DESCRIPTION  "Reverse bytes" 
		::={ acosSlbPassthroughS 5 } 

		slbPassthroughTotalRevPackets OBJECT-TYPE
		SYNTAX  CounterBasedGauge64 
		MAX-ACCESS read-only 
		STATUS current
		DESCRIPTION  "Reverse packets" 
		::={ acosSlbPassthroughS 6 } 

		currPconn OBJECT-TYPE
		SYNTAX  CounterBasedGauge64 
		MAX-ACCESS read-only 
		STATUS current
		DESCRIPTION  "Persistent connections" 
		::={ acosSlbPassthroughS 7 } 

acosSlbMysql                        OBJECT IDENTIFIER ::= { acosSlb 38 }
acosSlbMysqlS                       OBJECT IDENTIFIER ::= { acosSlbMysql 1 }

		slbMysqlCurrProxy OBJECT-TYPE
		SYNTAX  CounterBasedGauge64 
		MAX-ACCESS read-only 
		STATUS current
		DESCRIPTION  "Curr Proxy Conns" 
		::={ acosSlbMysqlS 1 } 

		slbMysqlTotalProxy OBJECT-TYPE
		SYNTAX  CounterBasedGauge64 
		MAX-ACCESS read-only 
		STATUS current
		DESCRIPTION  "Total Proxy Conns" 
		::={ acosSlbMysqlS 2 } 

		slbMysqlCurrBeEnc OBJECT-TYPE
		SYNTAX  CounterBasedGauge64 
		MAX-ACCESS read-only 
		STATUS current
		DESCRIPTION  "Curr BE Encryption Conns" 
		::={ acosSlbMysqlS 3 } 

		slbMysqlTotalBeEnc OBJECT-TYPE
		SYNTAX  CounterBasedGauge64 
		MAX-ACCESS read-only 
		STATUS current
		DESCRIPTION  "Total BE Encryption Conns" 
		::={ acosSlbMysqlS 4 } 

		slbMysqlCurrFeEnc OBJECT-TYPE
		SYNTAX  CounterBasedGauge64 
		MAX-ACCESS read-only 
		STATUS current
		DESCRIPTION  "Curr FE Encryption Conns" 
		::={ acosSlbMysqlS 5 } 

		slbMysqlTotalFeEnc OBJECT-TYPE
		SYNTAX  CounterBasedGauge64 
		MAX-ACCESS read-only 
		STATUS current
		DESCRIPTION  "Total FE Encryption Conns" 
		::={ acosSlbMysqlS 6 } 

		slbMysqlClientFin OBJECT-TYPE
		SYNTAX  CounterBasedGauge64 
		MAX-ACCESS read-only 
		STATUS current
		DESCRIPTION  "Client FIN" 
		::={ acosSlbMysqlS 7 } 

		slbMysqlServerFin OBJECT-TYPE
		SYNTAX  CounterBasedGauge64 
		MAX-ACCESS read-only 
		STATUS current
		DESCRIPTION  "Server FIN" 
		::={ acosSlbMysqlS 8 } 

		slbMysqlSessionErr OBJECT-TYPE
		SYNTAX  CounterBasedGauge64 
		MAX-ACCESS read-only 
		STATUS current
		DESCRIPTION  "Session err" 
		::={ acosSlbMysqlS 9 } 

		slbMysqlQueries OBJECT-TYPE
		SYNTAX  CounterBasedGauge64 
		MAX-ACCESS read-only 
		STATUS current
		DESCRIPTION  "DB Queries" 
		::={ acosSlbMysqlS 10 } 

		slbMysqlCommands OBJECT-TYPE
		SYNTAX  CounterBasedGauge64 
		MAX-ACCESS read-only 
		STATUS current
		DESCRIPTION  "DB commands reply" 
		::={ acosSlbMysqlS 11 } 

acosSlbMssql                        OBJECT IDENTIFIER ::= { acosSlb 39 }
acosSlbMssqlS                       OBJECT IDENTIFIER ::= { acosSlbMssql 1 }

		currProxy OBJECT-TYPE
		SYNTAX  CounterBasedGauge64 
		MAX-ACCESS read-only 
		STATUS current
		DESCRIPTION  "Curr Proxy Conns" 
		::={ acosSlbMssqlS 1 } 

		totalProxy OBJECT-TYPE
		SYNTAX  CounterBasedGauge64 
		MAX-ACCESS read-only 
		STATUS current
		DESCRIPTION  "Total Proxy Conns" 
		::={ acosSlbMssqlS 2 } 

		currBeEnc OBJECT-TYPE
		SYNTAX  CounterBasedGauge64 
		MAX-ACCESS read-only 
		STATUS current
		DESCRIPTION  "Curr BE Encryption Conns" 
		::={ acosSlbMssqlS 3 } 

		totalBeEnc OBJECT-TYPE
		SYNTAX  CounterBasedGauge64 
		MAX-ACCESS read-only 
		STATUS current
		DESCRIPTION  "Total BE Encryption Conns" 
		::={ acosSlbMssqlS 4 } 

		currFeEnc OBJECT-TYPE
		SYNTAX  CounterBasedGauge64 
		MAX-ACCESS read-only 
		STATUS current
		DESCRIPTION  "Curr FE Encryption Conns" 
		::={ acosSlbMssqlS 5 } 

		totalFeEnc OBJECT-TYPE
		SYNTAX  CounterBasedGauge64 
		MAX-ACCESS read-only 
		STATUS current
		DESCRIPTION  "Total FE Encryption Conns" 
		::={ acosSlbMssqlS 6 } 

		clientFin OBJECT-TYPE
		SYNTAX  CounterBasedGauge64 
		MAX-ACCESS read-only 
		STATUS current
		DESCRIPTION  "Client FIN" 
		::={ acosSlbMssqlS 7 } 

		serverFin OBJECT-TYPE
		SYNTAX  CounterBasedGauge64 
		MAX-ACCESS read-only 
		STATUS current
		DESCRIPTION  "Server FIN" 
		::={ acosSlbMssqlS 8 } 

		sessionErr OBJECT-TYPE
		SYNTAX  CounterBasedGauge64 
		MAX-ACCESS read-only 
		STATUS current
		DESCRIPTION  "Session err" 
		::={ acosSlbMssqlS 9 } 

		queries OBJECT-TYPE
		SYNTAX  CounterBasedGauge64 
		MAX-ACCESS read-only 
		STATUS current
		DESCRIPTION  "DB Queries" 
		::={ acosSlbMssqlS 10 } 

		commands OBJECT-TYPE
		SYNTAX  CounterBasedGauge64 
		MAX-ACCESS read-only 
		STATUS current
		DESCRIPTION  "DB commands reply" 
		::={ acosSlbMssqlS 11 } 

		authSuccess OBJECT-TYPE
		SYNTAX  CounterBasedGauge64 
		MAX-ACCESS read-only 
		STATUS current
		DESCRIPTION  "Authentication Success" 
		::={ acosSlbMssqlS 12 } 

		authFailure OBJECT-TYPE
		SYNTAX  CounterBasedGauge64 
		MAX-ACCESS read-only 
		STATUS current
		DESCRIPTION  "Authentication Failure" 
		::={ acosSlbMssqlS 13 } 

acosSlbCrlSrcip                     OBJECT IDENTIFIER ::= { acosSlb 40 }
acosSlbCrlSrcipS                    OBJECT IDENTIFIER ::= { acosSlbCrlSrcip 1 }

		sessionsAlloc OBJECT-TYPE
		SYNTAX  CounterBasedGauge64 
		MAX-ACCESS read-only 
		STATUS current
		DESCRIPTION  "Sessions allocated" 
		::={ acosSlbCrlSrcipS 1 } 

		sessionsFreed OBJECT-TYPE
		SYNTAX  CounterBasedGauge64 
		MAX-ACCESS read-only 
		STATUS current
		DESCRIPTION  "Sessions freed" 
		::={ acosSlbCrlSrcipS 2 } 

		outOfSessions OBJECT-TYPE
		SYNTAX  CounterBasedGauge64 
		MAX-ACCESS read-only 
		STATUS current
		DESCRIPTION  "Out of sessions" 
		::={ acosSlbCrlSrcipS 3 } 

		tooManySessions OBJECT-TYPE
		SYNTAX  CounterBasedGauge64 
		MAX-ACCESS read-only 
		STATUS current
		DESCRIPTION  "Too many sessions consumed" 
		::={ acosSlbCrlSrcipS 4 } 

		called OBJECT-TYPE
		SYNTAX  CounterBasedGauge64 
		MAX-ACCESS read-only 
		STATUS current
		DESCRIPTION  "Threshold check count" 
		::={ acosSlbCrlSrcipS 5 } 

		permitted OBJECT-TYPE
		SYNTAX  CounterBasedGauge64 
		MAX-ACCESS read-only 
		STATUS current
		DESCRIPTION  "Honor threshold  count" 
		::={ acosSlbCrlSrcipS 6 } 

		thresholdExceed OBJECT-TYPE
		SYNTAX  CounterBasedGauge64 
		MAX-ACCESS read-only 
		STATUS current
		DESCRIPTION  "Threshold exceeded count" 
		::={ acosSlbCrlSrcipS 7 } 

		lockoutDrop OBJECT-TYPE
		SYNTAX  CounterBasedGauge64 
		MAX-ACCESS read-only 
		STATUS current
		DESCRIPTION  "Lockout drops" 
		::={ acosSlbCrlSrcipS 8 } 

		logMsgSent OBJECT-TYPE
		SYNTAX  CounterBasedGauge64 
		MAX-ACCESS read-only 
		STATUS current
		DESCRIPTION  "Log messages sent" 
		::={ acosSlbCrlSrcipS 9 } 

acosSlbGenericProxy                 OBJECT IDENTIFIER ::= { acosSlb 41 }
acosSlbGenericProxyS                OBJECT IDENTIFIER ::= { acosSlbGenericProxy 1 }

		slbGenericProxyNum OBJECT-TYPE
		SYNTAX  CounterBasedGauge64 
		MAX-ACCESS read-only 
		STATUS current
		DESCRIPTION  "Number" 
		::={ acosSlbGenericProxyS 1 } 

		slbGenericProxyCurr OBJECT-TYPE
		SYNTAX  CounterBasedGauge64 
		MAX-ACCESS read-only 
		STATUS current
		DESCRIPTION  "Current" 
		::={ acosSlbGenericProxyS 2 } 

		slbGenericProxyTotal OBJECT-TYPE
		SYNTAX  CounterBasedGauge64 
		MAX-ACCESS read-only 
		STATUS current
		DESCRIPTION  "Total" 
		::={ acosSlbGenericProxyS 3 } 

		slbGenericProxySvrselFail OBJECT-TYPE
		SYNTAX  CounterBasedGauge64 
		MAX-ACCESS read-only 
		STATUS current
		DESCRIPTION  "Number of server selection failed" 
		::={ acosSlbGenericProxyS 4 } 

		slbGenericProxyNoRoute OBJECT-TYPE
		SYNTAX  CounterBasedGauge64 
		MAX-ACCESS read-only 
		STATUS current
		DESCRIPTION  "Number of no routes" 
		::={ acosSlbGenericProxyS 5 } 

		slbGenericProxySnatFail OBJECT-TYPE
		SYNTAX  CounterBasedGauge64 
		MAX-ACCESS read-only 
		STATUS current
		DESCRIPTION  "Number of snat failures" 
		::={ acosSlbGenericProxyS 6 } 

		slbGenericProxyClientFail OBJECT-TYPE
		SYNTAX  CounterBasedGauge64 
		MAX-ACCESS read-only 
		STATUS current
		DESCRIPTION  "Number of client failures" 
		::={ acosSlbGenericProxyS 7 } 

		slbGenericProxyServerFail OBJECT-TYPE
		SYNTAX  CounterBasedGauge64 
		MAX-ACCESS read-only 
		STATUS current
		DESCRIPTION  "Number of server failures" 
		::={ acosSlbGenericProxyS 8 } 

		slbGenericProxyNoSess OBJECT-TYPE
		SYNTAX  CounterBasedGauge64 
		MAX-ACCESS read-only 
		STATUS current
		DESCRIPTION  "Number of no sessions" 
		::={ acosSlbGenericProxyS 9 } 

		slbGenericProxyUserSession OBJECT-TYPE
		SYNTAX  CounterBasedGauge64 
		MAX-ACCESS read-only 
		STATUS current
		DESCRIPTION  "Number of user sessions" 
		::={ acosSlbGenericProxyS 10 } 

		slbGenericProxyAcrOUt OBJECT-TYPE
		SYNTAX  CounterBasedGauge64 
		MAX-ACCESS read-only 
		STATUS current
		DESCRIPTION  "Number of ACRs out" 
		::={ acosSlbGenericProxyS 11 } 

		slbGenericProxyAcrIn OBJECT-TYPE
		SYNTAX  CounterBasedGauge64 
		MAX-ACCESS read-only 
		STATUS current
		DESCRIPTION  "Number of ACRs in" 
		::={ acosSlbGenericProxyS 12 } 

		slbGenericProxyAcaOut OBJECT-TYPE
		SYNTAX  CounterBasedGauge64 
		MAX-ACCESS read-only 
		STATUS current
		DESCRIPTION  "Number of ACAs out" 
		::={ acosSlbGenericProxyS 13 } 

		slbGenericProxyAcaIn OBJECT-TYPE
		SYNTAX  CounterBasedGauge64 
		MAX-ACCESS read-only 
		STATUS current
		DESCRIPTION  "Number of ACAs in" 
		::={ acosSlbGenericProxyS 14 } 

		slbGenericProxyCeaOut OBJECT-TYPE
		SYNTAX  CounterBasedGauge64 
		MAX-ACCESS read-only 
		STATUS current
		DESCRIPTION  "Number of CEAs out" 
		::={ acosSlbGenericProxyS 15 } 

		slbGenericProxyCeaIn OBJECT-TYPE
		SYNTAX  CounterBasedGauge64 
		MAX-ACCESS read-only 
		STATUS current
		DESCRIPTION  "Number of CEAs in" 
		::={ acosSlbGenericProxyS 16 } 

		slbGenericProxyCerOut OBJECT-TYPE
		SYNTAX  CounterBasedGauge64 
		MAX-ACCESS read-only 
		STATUS current
		DESCRIPTION  "Number of CERs out" 
		::={ acosSlbGenericProxyS 17 } 

		slbGenericProxyCerIn OBJECT-TYPE
		SYNTAX  CounterBasedGauge64 
		MAX-ACCESS read-only 
		STATUS current
		DESCRIPTION  "Number of CERs in" 
		::={ acosSlbGenericProxyS 18 } 

		slbGenericProxyDwrOut OBJECT-TYPE
		SYNTAX  CounterBasedGauge64 
		MAX-ACCESS read-only 
		STATUS current
		DESCRIPTION  "Number of DWRs out" 
		::={ acosSlbGenericProxyS 19 } 

		slbGenericProxyDwrIn OBJECT-TYPE
		SYNTAX  CounterBasedGauge64 
		MAX-ACCESS read-only 
		STATUS current
		DESCRIPTION  "Number of DWRs in" 
		::={ acosSlbGenericProxyS 20 } 

		slbGenericProxyDwaOut OBJECT-TYPE
		SYNTAX  CounterBasedGauge64 
		MAX-ACCESS read-only 
		STATUS current
		DESCRIPTION  "Number of DWAs out" 
		::={ acosSlbGenericProxyS 21 } 

		slbGenericProxyDwaIn OBJECT-TYPE
		SYNTAX  CounterBasedGauge64 
		MAX-ACCESS read-only 
		STATUS current
		DESCRIPTION  "Number of DWAs in" 
		::={ acosSlbGenericProxyS 22 } 

		slbGenericProxyStrOut OBJECT-TYPE
		SYNTAX  CounterBasedGauge64 
		MAX-ACCESS read-only 
		STATUS current
		DESCRIPTION  "Number of STRs out" 
		::={ acosSlbGenericProxyS 23 } 

		slbGenericProxyStrIn OBJECT-TYPE
		SYNTAX  CounterBasedGauge64 
		MAX-ACCESS read-only 
		STATUS current
		DESCRIPTION  "Number of STRs in" 
		::={ acosSlbGenericProxyS 24 } 

		slbGenericProxyStaOut OBJECT-TYPE
		SYNTAX  CounterBasedGauge64 
		MAX-ACCESS read-only 
		STATUS current
		DESCRIPTION  "Number of STAs out" 
		::={ acosSlbGenericProxyS 25 } 

		slbGenericProxyStaIn OBJECT-TYPE
		SYNTAX  CounterBasedGauge64 
		MAX-ACCESS read-only 
		STATUS current
		DESCRIPTION  "Number of STAs in" 
		::={ acosSlbGenericProxyS 26 } 

		slbGenericProxyAsrOut OBJECT-TYPE
		SYNTAX  CounterBasedGauge64 
		MAX-ACCESS read-only 
		STATUS current
		DESCRIPTION  "Number of ASRs out" 
		::={ acosSlbGenericProxyS 27 } 

		slbGenericProxyAsrIn OBJECT-TYPE
		SYNTAX  CounterBasedGauge64 
		MAX-ACCESS read-only 
		STATUS current
		DESCRIPTION  "Number of ASRs in" 
		::={ acosSlbGenericProxyS 28 } 

		slbGenericProxyAsaOut OBJECT-TYPE
		SYNTAX  CounterBasedGauge64 
		MAX-ACCESS read-only 
		STATUS current
		DESCRIPTION  "Number of ASAs out" 
		::={ acosSlbGenericProxyS 29 } 

		slbGenericProxyAsaIn OBJECT-TYPE
		SYNTAX  CounterBasedGauge64 
		MAX-ACCESS read-only 
		STATUS current
		DESCRIPTION  "Number of ASAs in" 
		::={ acosSlbGenericProxyS 30 } 

		slbGenericProxyOtherOut OBJECT-TYPE
		SYNTAX  CounterBasedGauge64 
		MAX-ACCESS read-only 
		STATUS current
		DESCRIPTION  "Number of other messages out" 
		::={ acosSlbGenericProxyS 31 } 

		slbGenericProxyOtherIn OBJECT-TYPE
		SYNTAX  CounterBasedGauge64 
		MAX-ACCESS read-only 
		STATUS current
		DESCRIPTION  "Number of other messages in" 
		::={ acosSlbGenericProxyS 32 } 

		totalHttpReqEnterGen OBJECT-TYPE
		SYNTAX  CounterBasedGauge64 
		MAX-ACCESS read-only 
		STATUS current
		DESCRIPTION  "Total number of HTTP requests enter generic proxy" 
		::={ acosSlbGenericProxyS 33 } 

		slbGenericProxyDiaFwdId OBJECT-TYPE
		SYNTAX  CounterBasedGauge64 
		MAX-ACCESS read-only 
		STATUS current
		DESCRIPTION  "Diameter mismatch fwd session id" 
		::={ acosSlbGenericProxyS 34 } 

		slbGenericProxyDiaRevId OBJECT-TYPE
		SYNTAX  CounterBasedGauge64 
		MAX-ACCESS read-only 
		STATUS current
		DESCRIPTION  "Diameter mismatch rev session id" 
		::={ acosSlbGenericProxyS 35 } 

		slbGenericProxyDiaUnkCmd OBJECT-TYPE
		SYNTAX  CounterBasedGauge64 
		MAX-ACCESS read-only 
		STATUS current
		DESCRIPTION  "Diameter unkown cmd code" 
		::={ acosSlbGenericProxyS 36 } 

		slbGenericProxyDiaNoID OBJECT-TYPE
		SYNTAX  CounterBasedGauge64 
		MAX-ACCESS read-only 
		STATUS current
		DESCRIPTION  "Diameter no session id avp" 
		::={ acosSlbGenericProxyS 37 } 

		slbGenericProxyDiaNoFwd OBJECT-TYPE
		SYNTAX  CounterBasedGauge64 
		MAX-ACCESS read-only 
		STATUS current
		DESCRIPTION  "Diameter no fwd tuple matched" 
		::={ acosSlbGenericProxyS 38 } 

		slbGenericProxyDiaNoRev OBJECT-TYPE
		SYNTAX  CounterBasedGauge64 
		MAX-ACCESS read-only 
		STATUS current
		DESCRIPTION  "Diameter no rev tuple matched" 
		::={ acosSlbGenericProxyS 39 } 

		slbGenericProxyDiaDcmsgFwdIn OBJECT-TYPE
		SYNTAX  CounterBasedGauge64 
		MAX-ACCESS read-only 
		STATUS current
		DESCRIPTION  "Diameter cross cpu fwd in" 
		::={ acosSlbGenericProxyS 40 } 

		slbGenericProxyDiaDcmsgFwdOut OBJECT-TYPE
		SYNTAX  CounterBasedGauge64 
		MAX-ACCESS read-only 
		STATUS current
		DESCRIPTION  "Diameter cross cpu fwd out" 
		::={ acosSlbGenericProxyS 41 } 

		slbGenericProxyDiaDcmsgRevIn OBJECT-TYPE
		SYNTAX  CounterBasedGauge64 
		MAX-ACCESS read-only 
		STATUS current
		DESCRIPTION  "Diameter cross cpu rev in" 
		::={ acosSlbGenericProxyS 42 } 

		slbGenericProxyDiaDcmsgRevOut OBJECT-TYPE
		SYNTAX  CounterBasedGauge64 
		MAX-ACCESS read-only 
		STATUS current
		DESCRIPTION  "Diameter cross cpu rev out" 
		::={ acosSlbGenericProxyS 43 } 

		slbGenericProxyDiaDcmsgErr OBJECT-TYPE
		SYNTAX  CounterBasedGauge64 
		MAX-ACCESS read-only 
		STATUS current
		DESCRIPTION  "Diameter cross cpu error" 
		::={ acosSlbGenericProxyS 44 } 

		slbGenericProxyDiaRetry OBJECT-TYPE
		SYNTAX  CounterBasedGauge64 
		MAX-ACCESS read-only 
		STATUS current
		DESCRIPTION  "Diameter retry client request" 
		::={ acosSlbGenericProxyS 45 } 

		slbGenericProxyDiaRetryFail OBJECT-TYPE
		SYNTAX  CounterBasedGauge64 
		MAX-ACCESS read-only 
		STATUS current
		DESCRIPTION  "Diameter retry client request fail" 
		::={ acosSlbGenericProxyS 46 } 

		slbGenericProxyReplyUnknownSessionID OBJECT-TYPE
		SYNTAX  CounterBasedGauge64 
		MAX-ACCESS read-only 
		STATUS current
		DESCRIPTION  "Reply with unknown session ID error info" 
		::={ acosSlbGenericProxyS 47 } 

		slbGenericProxyCcrOut OBJECT-TYPE
		SYNTAX  CounterBasedGauge64 
		MAX-ACCESS read-only 
		STATUS current
		DESCRIPTION  "Number of CCRs out" 
		::={ acosSlbGenericProxyS 48 } 

		slbGenericProxyCcrIn OBJECT-TYPE
		SYNTAX  CounterBasedGauge64 
		MAX-ACCESS read-only 
		STATUS current
		DESCRIPTION  "Number of CCRs in" 
		::={ acosSlbGenericProxyS 49 } 

		slbGenericProxyCcaOut OBJECT-TYPE
		SYNTAX  CounterBasedGauge64 
		MAX-ACCESS read-only 
		STATUS current
		DESCRIPTION  "Number of CCAs out" 
		::={ acosSlbGenericProxyS 50 } 

		slbGenericProxyCcaIn OBJECT-TYPE
		SYNTAX  CounterBasedGauge64 
		MAX-ACCESS read-only 
		STATUS current
		DESCRIPTION  "Number of CCAs in" 
		::={ acosSlbGenericProxyS 51 } 

		slbGenericProxyCcrI OBJECT-TYPE
		SYNTAX  CounterBasedGauge64 
		MAX-ACCESS read-only 
		STATUS current
		DESCRIPTION  "Number of CCRs initial" 
		::={ acosSlbGenericProxyS 52 } 

		slbGenericProxyCcrU OBJECT-TYPE
		SYNTAX  CounterBasedGauge64 
		MAX-ACCESS read-only 
		STATUS current
		DESCRIPTION  "Number of CCRs update" 
		::={ acosSlbGenericProxyS 53 } 

		slbGenericProxyCcrT OBJECT-TYPE
		SYNTAX  CounterBasedGauge64 
		MAX-ACCESS read-only 
		STATUS current
		DESCRIPTION  "Number of CCRs terminate" 
		::={ acosSlbGenericProxyS 54 } 

		slbGenericProxyCcaT OBJECT-TYPE
		SYNTAX  CounterBasedGauge64 
		MAX-ACCESS read-only 
		STATUS current
		DESCRIPTION  "Number of CCAs terminate" 
		::={ acosSlbGenericProxyS 55 } 

		slbGenericProxyTermCCAT OBJECT-TYPE
		SYNTAX  CounterBasedGauge64 
		MAX-ACCESS read-only 
		STATUS current
		DESCRIPTION  "Diameter terminate on cca_t" 
		::={ acosSlbGenericProxyS 56 } 

		slbGenericProxyForwardUnknownSessionID OBJECT-TYPE
		SYNTAX  CounterBasedGauge64 
		MAX-ACCESS read-only 
		STATUS current
		DESCRIPTION  "Forward server side message with unknown session id" 
		::={ acosSlbGenericProxyS 57 } 

		slbGenericProxyUpdateLatestServer OBJECT-TYPE
		SYNTAX  CounterBasedGauge64 
		MAX-ACCESS read-only 
		STATUS current
		DESCRIPTION  "Update to the latest server that used a session id" 
		::={ acosSlbGenericProxyS 58 } 

		slbGenericProxyClientSelectFail OBJECT-TYPE
		SYNTAX  CounterBasedGauge64 
		MAX-ACCESS read-only 
		STATUS current
		DESCRIPTION  "Fail to select client" 
		::={ acosSlbGenericProxyS 59 } 

		slbGenericProxyCloseConnWhenVportDown OBJECT-TYPE
		SYNTAX  CounterBasedGauge64 
		MAX-ACCESS read-only 
		STATUS current
		DESCRIPTION  "Close client conn when virtual port is down" 
		::={ acosSlbGenericProxyS 60 } 

		slbGenericProxyInvalidAVP OBJECT-TYPE
		SYNTAX  CounterBasedGauge64 
		MAX-ACCESS read-only 
		STATUS current
		DESCRIPTION  "AVP value contains illegal chars" 
		::={ acosSlbGenericProxyS 61 } 

		slbGenericProxyReselectFwdTuple OBJECT-TYPE
		SYNTAX  CounterBasedGauge64 
		MAX-ACCESS read-only 
		STATUS current
		DESCRIPTION  "Original client tuple does not exist so reselect another one" 
		::={ acosSlbGenericProxyS 62 } 

		slbGenericProxyReselectFwdTupleOtherCPU OBJECT-TYPE
		SYNTAX  CounterBasedGauge64 
		MAX-ACCESS read-only 
		STATUS current
		DESCRIPTION  "Original client tuple does not exist so reselect another one on other CPUs" 
		::={ acosSlbGenericProxyS 63 } 

		slbGenericProxyReselectRevTuple OBJECT-TYPE
		SYNTAX  CounterBasedGauge64 
		MAX-ACCESS read-only 
		STATUS current
		DESCRIPTION  "Original server tuple does not exist so reselect another one" 
		::={ acosSlbGenericProxyS 64 } 

		slbGenericProxyConnClosedByClient OBJECT-TYPE
		SYNTAX  CounterBasedGauge64 
		MAX-ACCESS read-only 
		STATUS current
		DESCRIPTION  "Client initiates TCP close/reset" 
		::={ acosSlbGenericProxyS 65 } 

		slbGenericProxyConnClosedByServer OBJECT-TYPE
		SYNTAX  CounterBasedGauge64 
		MAX-ACCESS read-only 
		STATUS current
		DESCRIPTION  "Server initiates TCP close/reset" 
		::={ acosSlbGenericProxyS 66 } 

		slbGenericProxyReplyInvalidAVPValue OBJECT-TYPE
		SYNTAX  CounterBasedGauge64 
		MAX-ACCESS read-only 
		STATUS current
		DESCRIPTION  "Reply with invalid AVP error info" 
		::={ acosSlbGenericProxyS 67 } 

		slbGenericProxyReplyUnableToDeliver OBJECT-TYPE
		SYNTAX  CounterBasedGauge64 
		MAX-ACCESS read-only 
		STATUS current
		DESCRIPTION  "Reply with unable to deliver error info" 
		::={ acosSlbGenericProxyS 68 } 

		slbGenericProxyReplyErrorInfoFail OBJECT-TYPE
		SYNTAX  CounterBasedGauge64 
		MAX-ACCESS read-only 
		STATUS current
		DESCRIPTION  "Fail to reply error info to peer" 
		::={ acosSlbGenericProxyS 69 } 

		slbGenericProxyDprOut OBJECT-TYPE
		SYNTAX  CounterBasedGauge64 
		MAX-ACCESS read-only 
		STATUS current
		DESCRIPTION  "Number of DPRs out" 
		::={ acosSlbGenericProxyS 70 } 

		slbGenericProxyDprIn OBJECT-TYPE
		SYNTAX  CounterBasedGauge64 
		MAX-ACCESS read-only 
		STATUS current
		DESCRIPTION  "Number of DPRs in" 
		::={ acosSlbGenericProxyS 71 } 

		slbGenericProxyDpaOut OBJECT-TYPE
		SYNTAX  CounterBasedGauge64 
		MAX-ACCESS read-only 
		STATUS current
		DESCRIPTION  "Number of DPAs out" 
		::={ acosSlbGenericProxyS 72 } 

		slbGenericProxyDpaIn OBJECT-TYPE
		SYNTAX  CounterBasedGauge64 
		MAX-ACCESS read-only 
		STATUS current
		DESCRIPTION  "Number of DPAs in" 
		::={ acosSlbGenericProxyS 73 } 

acosSlbDns                          OBJECT IDENTIFIER ::= { acosSlb 42 }
acosSlbDnsS                         OBJECT IDENTIFIER ::= { acosSlbDns 1 }

		slbReq OBJECT-TYPE
		SYNTAX  CounterBasedGauge64 
		MAX-ACCESS read-only 
		STATUS current
		DESCRIPTION  "No. of requests" 
		::={ acosSlbDnsS 1 } 

		slbResp OBJECT-TYPE
		SYNTAX  CounterBasedGauge64 
		MAX-ACCESS read-only 
		STATUS current
		DESCRIPTION  "No. of responses" 
		::={ acosSlbDnsS 2 } 

		slbNoResp OBJECT-TYPE
		SYNTAX  CounterBasedGauge64 
		MAX-ACCESS read-only 
		STATUS current
		DESCRIPTION  "No. of requests with no response" 
		::={ acosSlbDnsS 3 } 

		slbReqRexmit OBJECT-TYPE
		SYNTAX  CounterBasedGauge64 
		MAX-ACCESS read-only 
		STATUS current
		DESCRIPTION  "No. of requests retransmit" 
		::={ acosSlbDnsS 4 } 

		slbRespNoMatch OBJECT-TYPE
		SYNTAX  CounterBasedGauge64 
		MAX-ACCESS read-only 
		STATUS current
		DESCRIPTION  "No. of requests and responses with no match" 
		::={ acosSlbDnsS 5 } 

		slbNoResource OBJECT-TYPE
		SYNTAX  CounterBasedGauge64 
		MAX-ACCESS read-only 
		STATUS current
		DESCRIPTION  "No. of resource failures" 
		::={ acosSlbDnsS 6 } 

		natReq OBJECT-TYPE
		SYNTAX  CounterBasedGauge64 
		MAX-ACCESS read-only 
		STATUS current
		DESCRIPTION  "(NAT) No. of requests" 
		::={ acosSlbDnsS 7 } 

		natResp OBJECT-TYPE
		SYNTAX  CounterBasedGauge64 
		MAX-ACCESS read-only 
		STATUS current
		DESCRIPTION  "(NAT) No. of responses" 
		::={ acosSlbDnsS 8 } 

		natNoResp OBJECT-TYPE
		SYNTAX  CounterBasedGauge64 
		MAX-ACCESS read-only 
		STATUS current
		DESCRIPTION  "(NAT) No. of resource failures" 
		::={ acosSlbDnsS 9 } 

		natReqRexmit OBJECT-TYPE
		SYNTAX  CounterBasedGauge64 
		MAX-ACCESS read-only 
		STATUS current
		DESCRIPTION  "(NAT) No. of request retransmits" 
		::={ acosSlbDnsS 10 } 

		natRespNoMatch OBJECT-TYPE
		SYNTAX  CounterBasedGauge64 
		MAX-ACCESS read-only 
		STATUS current
		DESCRIPTION  "(NAT) No. of requests with no response" 
		::={ acosSlbDnsS 11 } 

		natNoResource OBJECT-TYPE
		SYNTAX  CounterBasedGauge64 
		MAX-ACCESS read-only 
		STATUS current
		DESCRIPTION  "(NAT) No. of resource failures" 
		::={ acosSlbDnsS 12 } 

		natXidReused OBJECT-TYPE
		SYNTAX  CounterBasedGauge64 
		MAX-ACCESS read-only 
		STATUS current
		DESCRIPTION  "(NAT) No. of requests reusing a transaction id" 
		::={ acosSlbDnsS 13 } 

		filterTypeDrop OBJECT-TYPE
		SYNTAX  CounterBasedGauge64 
		MAX-ACCESS read-only 
		STATUS current
		DESCRIPTION  "Total Query Type Drop" 
		::={ acosSlbDnsS 14 } 

		filterClassDrop OBJECT-TYPE
		SYNTAX  CounterBasedGauge64 
		MAX-ACCESS read-only 
		STATUS current
		DESCRIPTION  "Total Query Class Drop" 
		::={ acosSlbDnsS 15 } 

		filterTypeAnyDrop OBJECT-TYPE
		SYNTAX  CounterBasedGauge64 
		MAX-ACCESS read-only 
		STATUS current
		DESCRIPTION  "Total Query ANY Type Drop" 
		::={ acosSlbDnsS 16 } 

		slbDnsClientSslSucc OBJECT-TYPE
		SYNTAX  CounterBasedGauge64 
		MAX-ACCESS read-only 
		STATUS current
		DESCRIPTION  "No. of client ssl success" 
		::={ acosSlbDnsS 17 } 

		slbDnsServerSslSucc OBJECT-TYPE
		SYNTAX  CounterBasedGauge64 
		MAX-ACCESS read-only 
		STATUS current
		DESCRIPTION  "No. of server ssl success" 
		::={ acosSlbDnsS 18 } 

		slbDnsUdpConn OBJECT-TYPE
		SYNTAX  CounterBasedGauge64 
		MAX-ACCESS read-only 
		STATUS current
		DESCRIPTION  "No. of backend udp connections" 
		::={ acosSlbDnsS 19 } 

		slbDnsUdpConnSucc OBJECT-TYPE
		SYNTAX  CounterBasedGauge64 
		MAX-ACCESS read-only 
		STATUS current
		DESCRIPTION  "No. of backend udp conn established" 
		::={ acosSlbDnsS 20 } 

		slbDnsPaddingToServerRemoved OBJECT-TYPE
		SYNTAX  CounterBasedGauge64 
		MAX-ACCESS read-only 
		STATUS current
		DESCRIPTION  "" 
		::={ acosSlbDnsS 21 } 

		slbDnsPaddingToClientAdded OBJECT-TYPE
		SYNTAX  CounterBasedGauge64 
		MAX-ACCESS read-only 
		STATUS current
		DESCRIPTION  "" 
		::={ acosSlbDnsS 22 } 

		slbDnsEdnsSubnetToServerRemoved OBJECT-TYPE
		SYNTAX  CounterBasedGauge64 
		MAX-ACCESS read-only 
		STATUS current
		DESCRIPTION  "" 
		::={ acosSlbDnsS 23 } 

		slbDnsUdpRetransmit OBJECT-TYPE
		SYNTAX  CounterBasedGauge64 
		MAX-ACCESS read-only 
		STATUS current
		DESCRIPTION  "" 
		::={ acosSlbDnsS 24 } 

		slbDnsUdpRetransmitFail OBJECT-TYPE
		SYNTAX  CounterBasedGauge64 
		MAX-ACCESS read-only 
		STATUS current
		DESCRIPTION  "" 
		::={ acosSlbDnsS 25 } 

		rpzActionDrop OBJECT-TYPE
		SYNTAX  CounterBasedGauge64 
		MAX-ACCESS read-only 
		STATUS current
		DESCRIPTION  "RPZ Action Drop" 
		::={ acosSlbDnsS 26 } 

		rpzActionPassThru OBJECT-TYPE
		SYNTAX  CounterBasedGauge64 
		MAX-ACCESS read-only 
		STATUS current
		DESCRIPTION  "RPZ Action Pass Through" 
		::={ acosSlbDnsS 27 } 

		rpzActionTcpOnly OBJECT-TYPE
		SYNTAX  CounterBasedGauge64 
		MAX-ACCESS read-only 
		STATUS current
		DESCRIPTION  "RPZ Action TCP Only" 
		::={ acosSlbDnsS 28 } 

		rpzActionNxdomain OBJECT-TYPE
		SYNTAX  CounterBasedGauge64 
		MAX-ACCESS read-only 
		STATUS current
		DESCRIPTION  "RPZ Action NXDOMAIN" 
		::={ acosSlbDnsS 29 } 

		rpzActionNodata OBJECT-TYPE
		SYNTAX  CounterBasedGauge64 
		MAX-ACCESS read-only 
		STATUS current
		DESCRIPTION  "RPZ Action NODATA" 
		::={ acosSlbDnsS 30 } 

		rpzActionLocalData OBJECT-TYPE
		SYNTAX  CounterBasedGauge64 
		MAX-ACCESS read-only 
		STATUS current
		DESCRIPTION  "RPZ Action Local Data" 
		::={ acosSlbDnsS 31 } 

		slbDrop OBJECT-TYPE
		SYNTAX  CounterBasedGauge64 
		MAX-ACCESS read-only 
		STATUS current
		DESCRIPTION  "DNS requests drop" 
		::={ acosSlbDnsS 32 } 

		natSlbDrop OBJECT-TYPE
		SYNTAX  CounterBasedGauge64 
		MAX-ACCESS read-only 
		STATUS current
		DESCRIPTION  "(NAT)DNS requests drop" 
		::={ acosSlbDnsS 33 } 

		invalidQLenToUdp OBJECT-TYPE
		SYNTAX  CounterBasedGauge64 
		MAX-ACCESS read-only 
		STATUS current
		DESCRIPTION  "invalid query length to conver to UDP" 
		::={ acosSlbDnsS 34 } 

		slbDnsEdnsEcsReceived OBJECT-TYPE
		SYNTAX  CounterBasedGauge64 
		MAX-ACCESS read-only 
		STATUS current
		DESCRIPTION  "Number of ecs from client received" 
		::={ acosSlbDnsS 35 } 

		slbDnsEdnsEcsInserted OBJECT-TYPE
		SYNTAX  CounterBasedGauge64 
		MAX-ACCESS read-only 
		STATUS current
		DESCRIPTION  "Number of ecs inserted" 
		::={ acosSlbDnsS 36 } 

acosSlbDnsCache                     OBJECT IDENTIFIER ::= { acosSlb 43 }
acosSlbDnsCacheS                    OBJECT IDENTIFIER ::= { acosSlbDnsCache 1 }

		totalQ OBJECT-TYPE
		SYNTAX  CounterBasedGauge64 
		MAX-ACCESS read-only 
		STATUS current
		DESCRIPTION  "Total query" 
		::={ acosSlbDnsCacheS 1 } 

		totalR OBJECT-TYPE
		SYNTAX  CounterBasedGauge64 
		MAX-ACCESS read-only 
		STATUS current
		DESCRIPTION  "Total server response" 
		::={ acosSlbDnsCacheS 2 } 

		hit OBJECT-TYPE
		SYNTAX  CounterBasedGauge64 
		MAX-ACCESS read-only 
		STATUS current
		DESCRIPTION  "Total cache hit" 
		::={ acosSlbDnsCacheS 3 } 

		badQ OBJECT-TYPE
		SYNTAX  CounterBasedGauge64 
		MAX-ACCESS read-only 
		STATUS current
		DESCRIPTION  "Query not passed" 
		::={ acosSlbDnsCacheS 4 } 

		encodeQ OBJECT-TYPE
		SYNTAX  CounterBasedGauge64 
		MAX-ACCESS read-only 
		STATUS current
		DESCRIPTION  "Query encoded" 
		::={ acosSlbDnsCacheS 5 } 

		multipleQ OBJECT-TYPE
		SYNTAX  CounterBasedGauge64 
		MAX-ACCESS read-only 
		STATUS current
		DESCRIPTION  "Query with multiple questions" 
		::={ acosSlbDnsCacheS 6 } 

		oversizeQ OBJECT-TYPE
		SYNTAX  CounterBasedGauge64 
		MAX-ACCESS read-only 
		STATUS current
		DESCRIPTION  "Query exceed cache size" 
		::={ acosSlbDnsCacheS 7 } 

		badR OBJECT-TYPE
		SYNTAX  CounterBasedGauge64 
		MAX-ACCESS read-only 
		STATUS current
		DESCRIPTION  "Response not passed" 
		::={ acosSlbDnsCacheS 8 } 

		oversizeR OBJECT-TYPE
		SYNTAX  CounterBasedGauge64 
		MAX-ACCESS read-only 
		STATUS current
		DESCRIPTION  "Response exceed cache size" 
		::={ acosSlbDnsCacheS 9 } 

		encodeR OBJECT-TYPE
		SYNTAX  CounterBasedGauge64 
		MAX-ACCESS read-only 
		STATUS current
		DESCRIPTION  "Response encoded" 
		::={ acosSlbDnsCacheS 10 } 

		multipleR OBJECT-TYPE
		SYNTAX  CounterBasedGauge64 
		MAX-ACCESS read-only 
		STATUS current
		DESCRIPTION  "Response with multiple questions" 
		::={ acosSlbDnsCacheS 11 } 

		answerR OBJECT-TYPE
		SYNTAX  CounterBasedGauge64 
		MAX-ACCESS read-only 
		STATUS current
		DESCRIPTION  "Response with multiple answers" 
		::={ acosSlbDnsCacheS 12 } 

		ttlR OBJECT-TYPE
		SYNTAX  CounterBasedGauge64 
		MAX-ACCESS read-only 
		STATUS current
		DESCRIPTION  "Response with short TTL" 
		::={ acosSlbDnsCacheS 13 } 

		ageout OBJECT-TYPE
		SYNTAX  CounterBasedGauge64 
		MAX-ACCESS read-only 
		STATUS current
		DESCRIPTION  "Total aged out" 
		::={ acosSlbDnsCacheS 14 } 

		badAnswer OBJECT-TYPE
		SYNTAX  CounterBasedGauge64 
		MAX-ACCESS read-only 
		STATUS current
		DESCRIPTION  "Bad Answer" 
		::={ acosSlbDnsCacheS 15 } 

		ageoutWeight OBJECT-TYPE
		SYNTAX  CounterBasedGauge64 
		MAX-ACCESS read-only 
		STATUS current
		DESCRIPTION  "Total aged for lower weight" 
		::={ acosSlbDnsCacheS 16 } 

		totalLog OBJECT-TYPE
		SYNTAX  CounterBasedGauge64 
		MAX-ACCESS read-only 
		STATUS current
		DESCRIPTION  "Total stats log sent" 
		::={ acosSlbDnsCacheS 17 } 

		totalAlloc OBJECT-TYPE
		SYNTAX  CounterBasedGauge64 
		MAX-ACCESS read-only 
		STATUS current
		DESCRIPTION  "Total allocated" 
		::={ acosSlbDnsCacheS 18 } 

		dnsTotalFreed OBJECT-TYPE
		SYNTAX  CounterBasedGauge64 
		MAX-ACCESS read-only 
		STATUS current
		DESCRIPTION  "Total freed" 
		::={ acosSlbDnsCacheS 19 } 

		currentAllocate OBJECT-TYPE
		SYNTAX  CounterBasedGauge64 
		MAX-ACCESS read-only 
		STATUS current
		DESCRIPTION  "Current allocate" 
		::={ acosSlbDnsCacheS 20 } 

		currentDataAllocate OBJECT-TYPE
		SYNTAX  CounterBasedGauge64 
		MAX-ACCESS read-only 
		STATUS current
		DESCRIPTION  "Current data allocate" 
		::={ acosSlbDnsCacheS 21 } 

		resolverQueueFull OBJECT-TYPE
		SYNTAX  CounterBasedGauge64 
		MAX-ACCESS read-only 
		STATUS current
		DESCRIPTION  "Resolver task queue full" 
		::={ acosSlbDnsCacheS 22 } 

		truncatedR OBJECT-TYPE
		SYNTAX  CounterBasedGauge64 
		MAX-ACCESS read-only 
		STATUS current
		DESCRIPTION  "Response with Truncation bit set" 
		::={ acosSlbDnsCacheS 23 } 

acosSlbDnsPersistentCache           OBJECT IDENTIFIER ::= { acosSlb 109 }
acosSlbDnsPersistentCacheS          OBJECT IDENTIFIER ::= { acosSlbDnsPersistentCache 1 }

		totalEntry OBJECT-TYPE
		SYNTAX  CounterBasedGauge64 
		MAX-ACCESS read-only 
		STATUS current
		DESCRIPTION  "Total persistent cache entry" 
		::={ acosSlbDnsPersistentCacheS 1 } 

		entrySaved OBJECT-TYPE
		SYNTAX  CounterBasedGauge64 
		MAX-ACCESS read-only 
		STATUS current
		DESCRIPTION  "Total saved cache entry" 
		::={ acosSlbDnsPersistentCacheS 2 } 

		entryDeleted OBJECT-TYPE
		SYNTAX  CounterBasedGauge64 
		MAX-ACCESS read-only 
		STATUS current
		DESCRIPTION  "Total deleted cache entry" 
		::={ acosSlbDnsPersistentCacheS 3 } 

		databaseBusy OBJECT-TYPE
		SYNTAX  CounterBasedGauge64 
		MAX-ACCESS read-only 
		STATUS current
		DESCRIPTION  "Database busy" 
		::={ acosSlbDnsPersistentCacheS 4 } 

		databaseError OBJECT-TYPE
		SYNTAX  CounterBasedGauge64 
		MAX-ACCESS read-only 
		STATUS current
		DESCRIPTION  "Database error" 
		::={ acosSlbDnsPersistentCacheS 5 } 

acosSlbFtpCtl                       OBJECT IDENTIFIER ::= { acosSlb 44 }
acosSlbFtpCtlS                      OBJECT IDENTIFIER ::= { acosSlbFtpCtl 1 }

		sessionsNum OBJECT-TYPE
		SYNTAX  CounterBasedGauge64 
		MAX-ACCESS read-only 
		STATUS current
		DESCRIPTION  "Total Control Sessions" 
		::={ acosSlbFtpCtlS 1 } 

		algPktsNum OBJECT-TYPE
		SYNTAX  CounterBasedGauge64 
		MAX-ACCESS read-only 
		STATUS current
		DESCRIPTION  "Total ALG packets" 
		::={ acosSlbFtpCtlS 2 } 

		algPktsXmittedNum OBJECT-TYPE
		SYNTAX  CounterBasedGauge64 
		MAX-ACCESS read-only 
		STATUS current
		DESCRIPTION  "ALG packets rexmitted" 
		::={ acosSlbFtpCtlS 3 } 

		algPortHelperCreated OBJECT-TYPE
		SYNTAX  CounterBasedGauge64 
		MAX-ACCESS read-only 
		STATUS current
		DESCRIPTION  "Total PORT helper sessions" 
		::={ acosSlbFtpCtlS 4 } 

		algPasvHelperCreated OBJECT-TYPE
		SYNTAX  CounterBasedGauge64 
		MAX-ACCESS read-only 
		STATUS current
		DESCRIPTION  "Total PASV helper sessions" 
		::={ acosSlbFtpCtlS 5 } 

		algPortHelperFreedUnused OBJECT-TYPE
		SYNTAX  CounterBasedGauge64 
		MAX-ACCESS read-only 
		STATUS current
		DESCRIPTION  "PORT helper freed unused" 
		::={ acosSlbFtpCtlS 6 } 

		algPasvHelperFreedUnused OBJECT-TYPE
		SYNTAX  CounterBasedGauge64 
		MAX-ACCESS read-only 
		STATUS current
		DESCRIPTION  "PASV helper freed unused" 
		::={ acosSlbFtpCtlS 7 } 

		algPortHelperNatFree OBJECT-TYPE
		SYNTAX  CounterBasedGauge64 
		MAX-ACCESS read-only 
		STATUS current
		DESCRIPTION  "PORT helper NAT free" 
		::={ acosSlbFtpCtlS 8 } 

acosSlbPersist                      OBJECT IDENTIFIER ::= { acosSlb 45 }
acosSlbPersistS                     OBJECT IDENTIFIER ::= { acosSlbPersist 1 }

		hashTblTrylockFail OBJECT-TYPE
		SYNTAX  CounterBasedGauge64 
		MAX-ACCESS read-only 
		STATUS current
		DESCRIPTION  "Hash tbl lock fail" 
		::={ acosSlbPersistS 1 } 

		hashTblCreateOk OBJECT-TYPE
		SYNTAX  CounterBasedGauge64 
		MAX-ACCESS read-only 
		STATUS current
		DESCRIPTION  "Hash tbl create ok" 
		::={ acosSlbPersistS 2 } 

		hashTblCreateFail OBJECT-TYPE
		SYNTAX  CounterBasedGauge64 
		MAX-ACCESS read-only 
		STATUS current
		DESCRIPTION  "Hash tbl create fail" 
		::={ acosSlbPersistS 3 } 

		hashTblFree OBJECT-TYPE
		SYNTAX  CounterBasedGauge64 
		MAX-ACCESS read-only 
		STATUS current
		DESCRIPTION  "Hash tbl free" 
		::={ acosSlbPersistS 4 } 

		hashTblRstUpdown OBJECT-TYPE
		SYNTAX  CounterBasedGauge64 
		MAX-ACCESS read-only 
		STATUS current
		DESCRIPTION  "Hash tbl reset (up/down)" 
		::={ acosSlbPersistS 5 } 

		hashTblRstAdddel OBJECT-TYPE
		SYNTAX  CounterBasedGauge64 
		MAX-ACCESS read-only 
		STATUS current
		DESCRIPTION  "Hash tbl reset (add/del)" 
		::={ acosSlbPersistS 6 } 

		urlHashPri OBJECT-TYPE
		SYNTAX  CounterBasedGauge64 
		MAX-ACCESS read-only 
		STATUS current
		DESCRIPTION  "URL hash persist (pri)" 
		::={ acosSlbPersistS 7 } 

		urlHashEnqueue OBJECT-TYPE
		SYNTAX  CounterBasedGauge64 
		MAX-ACCESS read-only 
		STATUS current
		DESCRIPTION  "URL hash persist (enQ)" 
		::={ acosSlbPersistS 8 } 

		urlHashSec OBJECT-TYPE
		SYNTAX  CounterBasedGauge64 
		MAX-ACCESS read-only 
		STATUS current
		DESCRIPTION  "URL hash persist (sec)" 
		::={ acosSlbPersistS 9 } 

		urlHashFail OBJECT-TYPE
		SYNTAX  CounterBasedGauge64 
		MAX-ACCESS read-only 
		STATUS current
		DESCRIPTION  "URL hash persist fail" 
		::={ acosSlbPersistS 10 } 

		headerHashPri OBJECT-TYPE
		SYNTAX  CounterBasedGauge64 
		MAX-ACCESS read-only 
		STATUS current
		DESCRIPTION  "Header hash persist(pri)" 
		::={ acosSlbPersistS 11 } 

		headerHashEnqueue OBJECT-TYPE
		SYNTAX  CounterBasedGauge64 
		MAX-ACCESS read-only 
		STATUS current
		DESCRIPTION  "Header hash persist(enQ)" 
		::={ acosSlbPersistS 12 } 

		headerHashSec OBJECT-TYPE
		SYNTAX  CounterBasedGauge64 
		MAX-ACCESS read-only 
		STATUS current
		DESCRIPTION  "Header hash persist(sec)" 
		::={ acosSlbPersistS 13 } 

		headerHashFail OBJECT-TYPE
		SYNTAX  CounterBasedGauge64 
		MAX-ACCESS read-only 
		STATUS current
		DESCRIPTION  "Header hash persist fail" 
		::={ acosSlbPersistS 14 } 

		srcIp OBJECT-TYPE
		SYNTAX  CounterBasedGauge64 
		MAX-ACCESS read-only 
		STATUS current
		DESCRIPTION  "SRC IP persist ok" 
		::={ acosSlbPersistS 15 } 

		srcIpEnqueue OBJECT-TYPE
		SYNTAX  CounterBasedGauge64 
		MAX-ACCESS read-only 
		STATUS current
		DESCRIPTION  "SRC IP persist enqueue" 
		::={ acosSlbPersistS 16 } 

		srcIpFail OBJECT-TYPE
		SYNTAX  CounterBasedGauge64 
		MAX-ACCESS read-only 
		STATUS current
		DESCRIPTION  "SRC IP persist fail" 
		::={ acosSlbPersistS 17 } 

		srcIpNewSessCache OBJECT-TYPE
		SYNTAX  CounterBasedGauge64 
		MAX-ACCESS read-only 
		STATUS current
		DESCRIPTION  "SRC IP new sess (cache)" 
		::={ acosSlbPersistS 18 } 

		srcIpNewSessCacheFail OBJECT-TYPE
		SYNTAX  CounterBasedGauge64 
		MAX-ACCESS read-only 
		STATUS current
		DESCRIPTION  "SRC IP new sess fail (c)" 
		::={ acosSlbPersistS 19 } 

		srcIpNewSessSel OBJECT-TYPE
		SYNTAX  CounterBasedGauge64 
		MAX-ACCESS read-only 
		STATUS current
		DESCRIPTION  "SRC IP new sess (select)" 
		::={ acosSlbPersistS 20 } 

		srcIpNewSessSelFail OBJECT-TYPE
		SYNTAX  CounterBasedGauge64 
		MAX-ACCESS read-only 
		STATUS current
		DESCRIPTION  "SRC IP new sess fail (s)" 
		::={ acosSlbPersistS 21 } 

		srcIpHashPri OBJECT-TYPE
		SYNTAX  CounterBasedGauge64 
		MAX-ACCESS read-only 
		STATUS current
		DESCRIPTION  "SRC IP hash persist(pri)" 
		::={ acosSlbPersistS 22 } 

		srcIpHashEnqueue OBJECT-TYPE
		SYNTAX  CounterBasedGauge64 
		MAX-ACCESS read-only 
		STATUS current
		DESCRIPTION  "SRC IP hash persist(enQ)" 
		::={ acosSlbPersistS 23 } 

		srcIpHashSec OBJECT-TYPE
		SYNTAX  CounterBasedGauge64 
		MAX-ACCESS read-only 
		STATUS current
		DESCRIPTION  "SRC IP hash persist(sec)" 
		::={ acosSlbPersistS 24 } 

		srcIpHashFail OBJECT-TYPE
		SYNTAX  CounterBasedGauge64 
		MAX-ACCESS read-only 
		STATUS current
		DESCRIPTION  "SRC IP hash persist fail" 
		::={ acosSlbPersistS 25 } 

		srcIpEnforce OBJECT-TYPE
		SYNTAX  CounterBasedGauge64 
		MAX-ACCESS read-only 
		STATUS current
		DESCRIPTION  "Enforce higher priority" 
		::={ acosSlbPersistS 26 } 

		dstIp OBJECT-TYPE
		SYNTAX  CounterBasedGauge64 
		MAX-ACCESS read-only 
		STATUS current
		DESCRIPTION  "DST IP persist ok" 
		::={ acosSlbPersistS 27 } 

		dstIpEnqueue OBJECT-TYPE
		SYNTAX  CounterBasedGauge64 
		MAX-ACCESS read-only 
		STATUS current
		DESCRIPTION  "DST IP persist enqueue" 
		::={ acosSlbPersistS 28 } 

		dstIpFail OBJECT-TYPE
		SYNTAX  CounterBasedGauge64 
		MAX-ACCESS read-only 
		STATUS current
		DESCRIPTION  "DST IP persist fail" 
		::={ acosSlbPersistS 29 } 

		dstIpNewSessCache OBJECT-TYPE
		SYNTAX  CounterBasedGauge64 
		MAX-ACCESS read-only 
		STATUS current
		DESCRIPTION  "DST IP new sess (cache)" 
		::={ acosSlbPersistS 30 } 

		dstIpNewSessCacheFail OBJECT-TYPE
		SYNTAX  CounterBasedGauge64 
		MAX-ACCESS read-only 
		STATUS current
		DESCRIPTION  "DST IP new sess fail (c)" 
		::={ acosSlbPersistS 31 } 

		dstIpNewSessSel OBJECT-TYPE
		SYNTAX  CounterBasedGauge64 
		MAX-ACCESS read-only 
		STATUS current
		DESCRIPTION  "DST IP new sess (select)" 
		::={ acosSlbPersistS 32 } 

		dstIpNewSessSelFail OBJECT-TYPE
		SYNTAX  CounterBasedGauge64 
		MAX-ACCESS read-only 
		STATUS current
		DESCRIPTION  "DST IP new sess fail (s)" 
		::={ acosSlbPersistS 33 } 

		dstIpHashPri OBJECT-TYPE
		SYNTAX  CounterBasedGauge64 
		MAX-ACCESS read-only 
		STATUS current
		DESCRIPTION  "DST IP hash persist(pri)" 
		::={ acosSlbPersistS 34 } 

		dstIpHashEnqueue OBJECT-TYPE
		SYNTAX  CounterBasedGauge64 
		MAX-ACCESS read-only 
		STATUS current
		DESCRIPTION  "DST IP hash persist(enQ)" 
		::={ acosSlbPersistS 35 } 

		dstIpHashSec OBJECT-TYPE
		SYNTAX  CounterBasedGauge64 
		MAX-ACCESS read-only 
		STATUS current
		DESCRIPTION  "DST IP hash persist(sec)" 
		::={ acosSlbPersistS 36 } 

		dstIpHashFail OBJECT-TYPE
		SYNTAX  CounterBasedGauge64 
		MAX-ACCESS read-only 
		STATUS current
		DESCRIPTION  "DST IP hash persist fail" 
		::={ acosSlbPersistS 37 } 

		csslSidNotFound OBJECT-TYPE
		SYNTAX  CounterBasedGauge64 
		MAX-ACCESS read-only 
		STATUS current
		DESCRIPTION  "Client SSL SID not found" 
		::={ acosSlbPersistS 38 } 

		csslSidMatch OBJECT-TYPE
		SYNTAX  CounterBasedGauge64 
		MAX-ACCESS read-only 
		STATUS current
		DESCRIPTION  "Client SSL SID match" 
		::={ acosSlbPersistS 39 } 

		csslSidNotMatch OBJECT-TYPE
		SYNTAX  CounterBasedGauge64 
		MAX-ACCESS read-only 
		STATUS current
		DESCRIPTION  "Client SSL SID not match" 
		::={ acosSlbPersistS 40 } 

		ssslSidNotFound OBJECT-TYPE
		SYNTAX  CounterBasedGauge64 
		MAX-ACCESS read-only 
		STATUS current
		DESCRIPTION  "Server SSL SID not found" 
		::={ acosSlbPersistS 41 } 

		ssslSidReset OBJECT-TYPE
		SYNTAX  CounterBasedGauge64 
		MAX-ACCESS read-only 
		STATUS current
		DESCRIPTION  "Server SSL SID reset" 
		::={ acosSlbPersistS 42 } 

		ssslSidMatch OBJECT-TYPE
		SYNTAX  CounterBasedGauge64 
		MAX-ACCESS read-only 
		STATUS current
		DESCRIPTION  "Server SSL SID match" 
		::={ acosSlbPersistS 43 } 

		ssslSidNotMatch OBJECT-TYPE
		SYNTAX  CounterBasedGauge64 
		MAX-ACCESS read-only 
		STATUS current
		DESCRIPTION  "Server SSL SID not match" 
		::={ acosSlbPersistS 44 } 

		sslSidPersistOk OBJECT-TYPE
		SYNTAX  CounterBasedGauge64 
		MAX-ACCESS read-only 
		STATUS current
		DESCRIPTION  "SSL SID persist ok" 
		::={ acosSlbPersistS 45 } 

		sslSidPersistFail OBJECT-TYPE
		SYNTAX  CounterBasedGauge64 
		MAX-ACCESS read-only 
		STATUS current
		DESCRIPTION  "SSL SID persist fail" 
		::={ acosSlbPersistS 46 } 

		sslSidSessionOk OBJECT-TYPE
		SYNTAX  CounterBasedGauge64 
		MAX-ACCESS read-only 
		STATUS current
		DESCRIPTION  "Create SSL SID ok" 
		::={ acosSlbPersistS 47 } 

		sslSidSessionFail OBJECT-TYPE
		SYNTAX  CounterBasedGauge64 
		MAX-ACCESS read-only 
		STATUS current
		DESCRIPTION  "Create SSL SID fail" 
		::={ acosSlbPersistS 48 } 

		cookiePersistOk OBJECT-TYPE
		SYNTAX  CounterBasedGauge64 
		MAX-ACCESS read-only 
		STATUS current
		DESCRIPTION  "Cookie persist ok" 
		::={ acosSlbPersistS 49 } 

		cookiePersistFail OBJECT-TYPE
		SYNTAX  CounterBasedGauge64 
		MAX-ACCESS read-only 
		STATUS current
		DESCRIPTION  "Cookie persist fail" 
		::={ acosSlbPersistS 50 } 

		cookieNotFound OBJECT-TYPE
		SYNTAX  CounterBasedGauge64 
		MAX-ACCESS read-only 
		STATUS current
		DESCRIPTION  "Persist cookie not found" 
		::={ acosSlbPersistS 51 } 

		cookiePassThru OBJECT-TYPE
		SYNTAX  CounterBasedGauge64 
		MAX-ACCESS read-only 
		STATUS current
		DESCRIPTION  "Persist cookie Pass-thru" 
		::={ acosSlbPersistS 52 } 

		cookieInvalid OBJECT-TYPE
		SYNTAX  CounterBasedGauge64 
		MAX-ACCESS read-only 
		STATUS current
		DESCRIPTION  "Invalid persist cookie" 
		::={ acosSlbPersistS 53 } 

acosSlbHttpProxy                    OBJECT IDENTIFIER ::= { acosSlb 46 }
acosSlbHttpProxyS                   OBJECT IDENTIFIER ::= { acosSlbHttpProxy 1 }

		num OBJECT-TYPE
		SYNTAX  CounterBasedGauge64 
		MAX-ACCESS read-only 
		STATUS current
		DESCRIPTION  "Num" 
		::={ acosSlbHttpProxyS 1 } 

		slbHttpProxyCurrProxy OBJECT-TYPE
		SYNTAX  CounterBasedGauge64 
		MAX-ACCESS read-only 
		STATUS current
		DESCRIPTION  "Curr Proxy Conns" 
		::={ acosSlbHttpProxyS 2 } 

		slbHttpProxyTotalProxy OBJECT-TYPE
		SYNTAX  CounterBasedGauge64 
		MAX-ACCESS read-only 
		STATUS current
		DESCRIPTION  "Total Proxy Conns" 
		::={ acosSlbHttpProxyS 3 } 

		slbHttpProxyReq OBJECT-TYPE
		SYNTAX  CounterBasedGauge64 
		MAX-ACCESS read-only 
		STATUS current
		DESCRIPTION  "HTTP requests" 
		::={ acosSlbHttpProxyS 4 } 

		slbHttpProxyReqSucc OBJECT-TYPE
		SYNTAX  CounterBasedGauge64 
		MAX-ACCESS read-only 
		STATUS current
		DESCRIPTION  "HTTP requests(succ)" 
		::={ acosSlbHttpProxyS 5 } 

		slbHttpProxyNoProxy OBJECT-TYPE
		SYNTAX  CounterBasedGauge64 
		MAX-ACCESS read-only 
		STATUS current
		DESCRIPTION  "No proxy error" 
		::={ acosSlbHttpProxyS 6 } 

		slbHttpProxyClientRst OBJECT-TYPE
		SYNTAX  CounterBasedGauge64 
		MAX-ACCESS read-only 
		STATUS current
		DESCRIPTION  "Client RST" 
		::={ acosSlbHttpProxyS 7 } 

		slbHttpProxyServerRst OBJECT-TYPE
		SYNTAX  CounterBasedGauge64 
		MAX-ACCESS read-only 
		STATUS current
		DESCRIPTION  "Server RST" 
		::={ acosSlbHttpProxyS 8 } 

		slbHttpProxyNotuple OBJECT-TYPE
		SYNTAX  CounterBasedGauge64 
		MAX-ACCESS read-only 
		STATUS current
		DESCRIPTION  "No tuple error" 
		::={ acosSlbHttpProxyS 9 } 

		slbHttpProxyParsereqFail OBJECT-TYPE
		SYNTAX  CounterBasedGauge64 
		MAX-ACCESS read-only 
		STATUS current
		DESCRIPTION  "Parse req fail" 
		::={ acosSlbHttpProxyS 10 } 

		slbHttpProxySvrselFail OBJECT-TYPE
		SYNTAX  CounterBasedGauge64 
		MAX-ACCESS read-only 
		STATUS current
		DESCRIPTION  "Server selection fail" 
		::={ acosSlbHttpProxyS 11 } 

		slbHttpProxyFwdreqFail OBJECT-TYPE
		SYNTAX  CounterBasedGauge64 
		MAX-ACCESS read-only 
		STATUS current
		DESCRIPTION  "Fwd req fail" 
		::={ acosSlbHttpProxyS 12 } 

		fwdreqFailBuff OBJECT-TYPE
		SYNTAX  CounterBasedGauge64 
		MAX-ACCESS read-only 
		STATUS current
		DESCRIPTION  "Fwd req fail - buff" 
		::={ acosSlbHttpProxyS 13 } 

		fwdreqFailRport OBJECT-TYPE
		SYNTAX  CounterBasedGauge64 
		MAX-ACCESS read-only 
		STATUS current
		DESCRIPTION  "Fwd req fail - rport" 
		::={ acosSlbHttpProxyS 14 } 

		fwdreqFailRoute OBJECT-TYPE
		SYNTAX  CounterBasedGauge64 
		MAX-ACCESS read-only 
		STATUS current
		DESCRIPTION  "Fwd req fail - route" 
		::={ acosSlbHttpProxyS 15 } 

		fwdreqFailPersist OBJECT-TYPE
		SYNTAX  CounterBasedGauge64 
		MAX-ACCESS read-only 
		STATUS current
		DESCRIPTION  "Fwd req fail - persist" 
		::={ acosSlbHttpProxyS 16 } 

		fwdreqFailServer OBJECT-TYPE
		SYNTAX  CounterBasedGauge64 
		MAX-ACCESS read-only 
		STATUS current
		DESCRIPTION  "Fwd req fail - server" 
		::={ acosSlbHttpProxyS 17 } 

		fwdreqFailTuple OBJECT-TYPE
		SYNTAX  CounterBasedGauge64 
		MAX-ACCESS read-only 
		STATUS current
		DESCRIPTION  "Fwd req fail - tuple" 
		::={ acosSlbHttpProxyS 18 } 

		slbHttpProxyFwdreqdataFail OBJECT-TYPE
		SYNTAX  CounterBasedGauge64 
		MAX-ACCESS read-only 
		STATUS current
		DESCRIPTION  "" 
		::={ acosSlbHttpProxyS 19 } 

		slbHttpProxyReqRetran OBJECT-TYPE
		SYNTAX  CounterBasedGauge64 
		MAX-ACCESS read-only 
		STATUS current
		DESCRIPTION  "Packets retrans" 
		::={ acosSlbHttpProxyS 20 } 

		slbHttpProxyReqOfo OBJECT-TYPE
		SYNTAX  CounterBasedGauge64 
		MAX-ACCESS read-only 
		STATUS current
		DESCRIPTION  "Packets ofo" 
		::={ acosSlbHttpProxyS 21 } 

		slbHttpProxyServerResel OBJECT-TYPE
		SYNTAX  CounterBasedGauge64 
		MAX-ACCESS read-only 
		STATUS current
		DESCRIPTION  "Server reselection" 
		::={ acosSlbHttpProxyS 22 } 

		slbHttpProxySvrPremClose OBJECT-TYPE
		SYNTAX  CounterBasedGauge64 
		MAX-ACCESS read-only 
		STATUS current
		DESCRIPTION  "Server premature close" 
		::={ acosSlbHttpProxyS 23 } 

		slbHttpProxyNewSvnConn OBJECT-TYPE
		SYNTAX  CounterBasedGauge64 
		MAX-ACCESS read-only 
		STATUS current
		DESCRIPTION  "Server conn made" 
		::={ acosSlbHttpProxyS 24 } 

		slbHttpProxySnatFail OBJECT-TYPE
		SYNTAX  CounterBasedGauge64 
		MAX-ACCESS read-only 
		STATUS current
		DESCRIPTION  "Source NAT failure" 
		::={ acosSlbHttpProxyS 25 } 

		tcpoutrst OBJECT-TYPE
		SYNTAX  CounterBasedGauge64 
		MAX-ACCESS read-only 
		STATUS current
		DESCRIPTION  "Out RSTs" 
		::={ acosSlbHttpProxyS 26 } 

		fullProxy OBJECT-TYPE
		SYNTAX  CounterBasedGauge64 
		MAX-ACCESS read-only 
		STATUS current
		DESCRIPTION  "Full proxy tot" 
		::={ acosSlbHttpProxyS 27 } 

		fullProxyPost OBJECT-TYPE
		SYNTAX  CounterBasedGauge64 
		MAX-ACCESS read-only 
		STATUS current
		DESCRIPTION  "Full proxy POST" 
		::={ acosSlbHttpProxyS 28 } 

		fullProxyPipeline OBJECT-TYPE
		SYNTAX  CounterBasedGauge64 
		MAX-ACCESS read-only 
		STATUS current
		DESCRIPTION  "Full proxy pipeline" 
		::={ acosSlbHttpProxyS 29 } 

		fullProxyFpgaErr OBJECT-TYPE
		SYNTAX  CounterBasedGauge64 
		MAX-ACCESS read-only 
		STATUS current
		DESCRIPTION  "Full proxy fpga err" 
		::={ acosSlbHttpProxyS 30 } 

		slbHttpProxyReqOverLimit OBJECT-TYPE
		SYNTAX  CounterBasedGauge64 
		MAX-ACCESS read-only 
		STATUS current
		DESCRIPTION  "Request over limit" 
		::={ acosSlbHttpProxyS 31 } 

		slbHttpProxyReqRateOverLimit OBJECT-TYPE
		SYNTAX  CounterBasedGauge64 
		MAX-ACCESS read-only 
		STATUS current
		DESCRIPTION  "Request rate over limit" 
		::={ acosSlbHttpProxyS 32 } 

		l4Switching OBJECT-TYPE
		SYNTAX  CounterBasedGauge64 
		MAX-ACCESS read-only 
		STATUS current
		DESCRIPTION  "L4 switching" 
		::={ acosSlbHttpProxyS 33 } 

		cookieSwitching OBJECT-TYPE
		SYNTAX  CounterBasedGauge64 
		MAX-ACCESS read-only 
		STATUS current
		DESCRIPTION  "Cookie switching" 
		::={ acosSlbHttpProxyS 34 } 

		aflexSwitching OBJECT-TYPE
		SYNTAX  CounterBasedGauge64 
		MAX-ACCESS read-only 
		STATUS current
		DESCRIPTION  "aFleX switching" 
		::={ acosSlbHttpProxyS 35 } 

		httpPolicySwitching OBJECT-TYPE
		SYNTAX  CounterBasedGauge64 
		MAX-ACCESS read-only 
		STATUS current
		DESCRIPTION  "HTTP Policy switching" 
		::={ acosSlbHttpProxyS 36 } 

		urlSwitching OBJECT-TYPE
		SYNTAX  CounterBasedGauge64 
		MAX-ACCESS read-only 
		STATUS current
		DESCRIPTION  "URL switching" 
		::={ acosSlbHttpProxyS 37 } 

		hostSwitching OBJECT-TYPE
		SYNTAX  CounterBasedGauge64 
		MAX-ACCESS read-only 
		STATUS current
		DESCRIPTION  "Host switching" 
		::={ acosSlbHttpProxyS 38 } 

		lbSwitching OBJECT-TYPE
		SYNTAX  CounterBasedGauge64 
		MAX-ACCESS read-only 
		STATUS current
		DESCRIPTION  "Normal LB switching" 
		::={ acosSlbHttpProxyS 39 } 

		l4SwitchingOk OBJECT-TYPE
		SYNTAX  CounterBasedGauge64 
		MAX-ACCESS read-only 
		STATUS current
		DESCRIPTION  "L4 switching (succ)" 
		::={ acosSlbHttpProxyS 40 } 

		cookieSwitchingOk OBJECT-TYPE
		SYNTAX  CounterBasedGauge64 
		MAX-ACCESS read-only 
		STATUS current
		DESCRIPTION  "Cookie switching (succ)" 
		::={ acosSlbHttpProxyS 41 } 

		aflexSwitchingOk OBJECT-TYPE
		SYNTAX  CounterBasedGauge64 
		MAX-ACCESS read-only 
		STATUS current
		DESCRIPTION  "aFleX switching (succ)" 
		::={ acosSlbHttpProxyS 42 } 

		httpPolicySwitchingOk OBJECT-TYPE
		SYNTAX  CounterBasedGauge64 
		MAX-ACCESS read-only 
		STATUS current
		DESCRIPTION  "HTTP Policy switching (succ)" 
		::={ acosSlbHttpProxyS 43 } 

		urlSwitchingOk OBJECT-TYPE
		SYNTAX  CounterBasedGauge64 
		MAX-ACCESS read-only 
		STATUS current
		DESCRIPTION  "URL switching (succ)" 
		::={ acosSlbHttpProxyS 44 } 

		hostSwitchingOk OBJECT-TYPE
		SYNTAX  CounterBasedGauge64 
		MAX-ACCESS read-only 
		STATUS current
		DESCRIPTION  "Host switching (succ)" 
		::={ acosSlbHttpProxyS 45 } 

		lbSwitchingOk OBJECT-TYPE
		SYNTAX  CounterBasedGauge64 
		MAX-ACCESS read-only 
		STATUS current
		DESCRIPTION  "Normal LB switch. (succ)" 
		::={ acosSlbHttpProxyS 46 } 

		l4SwitchingEnqueue OBJECT-TYPE
		SYNTAX  CounterBasedGauge64 
		MAX-ACCESS read-only 
		STATUS current
		DESCRIPTION  "L4 switching (enQ)" 
		::={ acosSlbHttpProxyS 47 } 

		cookieSwitchingEnqueue OBJECT-TYPE
		SYNTAX  CounterBasedGauge64 
		MAX-ACCESS read-only 
		STATUS current
		DESCRIPTION  "Cookie switching (enQ)" 
		::={ acosSlbHttpProxyS 48 } 

		aflexSwitchingEnqueue OBJECT-TYPE
		SYNTAX  CounterBasedGauge64 
		MAX-ACCESS read-only 
		STATUS current
		DESCRIPTION  "aFleX switching (enQ)" 
		::={ acosSlbHttpProxyS 49 } 

		httpPolicySwitchingEnqueue OBJECT-TYPE
		SYNTAX  CounterBasedGauge64 
		MAX-ACCESS read-only 
		STATUS current
		DESCRIPTION  "HTTP Policy switching (enQ)" 
		::={ acosSlbHttpProxyS 50 } 

		urlSwitchingEnqueue OBJECT-TYPE
		SYNTAX  CounterBasedGauge64 
		MAX-ACCESS read-only 
		STATUS current
		DESCRIPTION  "URL switching (enQ)" 
		::={ acosSlbHttpProxyS 51 } 

		hostSwitchingEnqueue OBJECT-TYPE
		SYNTAX  CounterBasedGauge64 
		MAX-ACCESS read-only 
		STATUS current
		DESCRIPTION  "Host switching (enQ)" 
		::={ acosSlbHttpProxyS 52 } 

		lbSwitchingEnqueue OBJECT-TYPE
		SYNTAX  CounterBasedGauge64 
		MAX-ACCESS read-only 
		STATUS current
		DESCRIPTION  "Normal LB switch. (enQ)" 
		::={ acosSlbHttpProxyS 53 } 

		retry503 OBJECT-TYPE
		SYNTAX  CounterBasedGauge64 
		MAX-ACCESS read-only 
		STATUS current
		DESCRIPTION  "Retry on 503" 
		::={ acosSlbHttpProxyS 54 } 

		aflexRetry OBJECT-TYPE
		SYNTAX  CounterBasedGauge64 
		MAX-ACCESS read-only 
		STATUS current
		DESCRIPTION  "aFleX http retry" 
		::={ acosSlbHttpProxyS 55 } 

		aflexLbReselect OBJECT-TYPE
		SYNTAX  CounterBasedGauge64 
		MAX-ACCESS read-only 
		STATUS current
		DESCRIPTION  "aFleX lb reselect" 
		::={ acosSlbHttpProxyS 56 } 

		aflexLbReselectOk OBJECT-TYPE
		SYNTAX  CounterBasedGauge64 
		MAX-ACCESS read-only 
		STATUS current
		DESCRIPTION  "aFleX lb reselect (succ)" 
		::={ acosSlbHttpProxyS 57 } 

		clientRstRequest OBJECT-TYPE
		SYNTAX  CounterBasedGauge64 
		MAX-ACCESS read-only 
		STATUS current
		DESCRIPTION  "Client RST - request" 
		::={ acosSlbHttpProxyS 58 } 

		clientRstConnecting OBJECT-TYPE
		SYNTAX  CounterBasedGauge64 
		MAX-ACCESS read-only 
		STATUS current
		DESCRIPTION  "Client RST - connecting" 
		::={ acosSlbHttpProxyS 59 } 

		clientRstConnected OBJECT-TYPE
		SYNTAX  CounterBasedGauge64 
		MAX-ACCESS read-only 
		STATUS current
		DESCRIPTION  "Client RST - connected" 
		::={ acosSlbHttpProxyS 60 } 

		clientRstResponse OBJECT-TYPE
		SYNTAX  CounterBasedGauge64 
		MAX-ACCESS read-only 
		STATUS current
		DESCRIPTION  "Client RST - response" 
		::={ acosSlbHttpProxyS 61 } 

		serverRstRequest OBJECT-TYPE
		SYNTAX  CounterBasedGauge64 
		MAX-ACCESS read-only 
		STATUS current
		DESCRIPTION  "Server RST - request" 
		::={ acosSlbHttpProxyS 62 } 

		serverRstConnecting OBJECT-TYPE
		SYNTAX  CounterBasedGauge64 
		MAX-ACCESS read-only 
		STATUS current
		DESCRIPTION  "Server RST - connecting" 
		::={ acosSlbHttpProxyS 63 } 

		serverRstConnected OBJECT-TYPE
		SYNTAX  CounterBasedGauge64 
		MAX-ACCESS read-only 
		STATUS current
		DESCRIPTION  "Server RST - connected" 
		::={ acosSlbHttpProxyS 64 } 

		serverRstResponse OBJECT-TYPE
		SYNTAX  CounterBasedGauge64 
		MAX-ACCESS read-only 
		STATUS current
		DESCRIPTION  "Server RST - response" 
		::={ acosSlbHttpProxyS 65 } 

		invalidHeader OBJECT-TYPE
		SYNTAX  CounterBasedGauge64 
		MAX-ACCESS read-only 
		STATUS current
		DESCRIPTION  "Invalid header" 
		::={ acosSlbHttpProxyS 66 } 

		tooManyHeaders OBJECT-TYPE
		SYNTAX  CounterBasedGauge64 
		MAX-ACCESS read-only 
		STATUS current
		DESCRIPTION  "Too many headers" 
		::={ acosSlbHttpProxyS 67 } 

		lineTooLong OBJECT-TYPE
		SYNTAX  CounterBasedGauge64 
		MAX-ACCESS read-only 
		STATUS current
		DESCRIPTION  "Line too long" 
		::={ acosSlbHttpProxyS 68 } 

		headerNameTooLong OBJECT-TYPE
		SYNTAX  CounterBasedGauge64 
		MAX-ACCESS read-only 
		STATUS current
		DESCRIPTION  "Header name too long" 
		::={ acosSlbHttpProxyS 69 } 

		wrongRespHeader OBJECT-TYPE
		SYNTAX  CounterBasedGauge64 
		MAX-ACCESS read-only 
		STATUS current
		DESCRIPTION  "Wrong response header" 
		::={ acosSlbHttpProxyS 70 } 

		headerInsert OBJECT-TYPE
		SYNTAX  CounterBasedGauge64 
		MAX-ACCESS read-only 
		STATUS current
		DESCRIPTION  "Header insert" 
		::={ acosSlbHttpProxyS 71 } 

		headerDelete OBJECT-TYPE
		SYNTAX  CounterBasedGauge64 
		MAX-ACCESS read-only 
		STATUS current
		DESCRIPTION  "Header delete" 
		::={ acosSlbHttpProxyS 72 } 

		insertClientIp OBJECT-TYPE
		SYNTAX  CounterBasedGauge64 
		MAX-ACCESS read-only 
		STATUS current
		DESCRIPTION  "Insert client IP" 
		::={ acosSlbHttpProxyS 73 } 

		negativeReqRemain OBJECT-TYPE
		SYNTAX  CounterBasedGauge64 
		MAX-ACCESS read-only 
		STATUS current
		DESCRIPTION  "Negative request remain" 
		::={ acosSlbHttpProxyS 74 } 

		negativeRespRemain OBJECT-TYPE
		SYNTAX  CounterBasedGauge64 
		MAX-ACCESS read-only 
		STATUS current
		DESCRIPTION  "Negative response remain" 
		::={ acosSlbHttpProxyS 75 } 

		largeCookie OBJECT-TYPE
		SYNTAX  CounterBasedGauge64 
		MAX-ACCESS read-only 
		STATUS current
		DESCRIPTION  "Large cookies" 
		::={ acosSlbHttpProxyS 76 } 

		largeCookieHeader OBJECT-TYPE
		SYNTAX  CounterBasedGauge64 
		MAX-ACCESS read-only 
		STATUS current
		DESCRIPTION  "Large cookie headers" 
		::={ acosSlbHttpProxyS 77 } 

		hugeCookie OBJECT-TYPE
		SYNTAX  CounterBasedGauge64 
		MAX-ACCESS read-only 
		STATUS current
		DESCRIPTION  "Huge cookies" 
		::={ acosSlbHttpProxyS 78 } 

		hugeCookieHeader OBJECT-TYPE
		SYNTAX  CounterBasedGauge64 
		MAX-ACCESS read-only 
		STATUS current
		DESCRIPTION  "Huge cookie headers" 
		::={ acosSlbHttpProxyS 79 } 

		parseCookieFail OBJECT-TYPE
		SYNTAX  CounterBasedGauge64 
		MAX-ACCESS read-only 
		STATUS current
		DESCRIPTION  "Parse cookie fail" 
		::={ acosSlbHttpProxyS 80 } 

		parseSetcookieFail OBJECT-TYPE
		SYNTAX  CounterBasedGauge64 
		MAX-ACCESS read-only 
		STATUS current
		DESCRIPTION  "Parse set-cookie fail" 
		::={ acosSlbHttpProxyS 81 } 

		asmCookieFail OBJECT-TYPE
		SYNTAX  CounterBasedGauge64 
		MAX-ACCESS read-only 
		STATUS current
		DESCRIPTION  "Assemble cookie fail" 
		::={ acosSlbHttpProxyS 82 } 

		asmCookieHeaderFail OBJECT-TYPE
		SYNTAX  CounterBasedGauge64 
		MAX-ACCESS read-only 
		STATUS current
		DESCRIPTION  "Asm cookie header fail" 
		::={ acosSlbHttpProxyS 83 } 

		asmSetcookieFail OBJECT-TYPE
		SYNTAX  CounterBasedGauge64 
		MAX-ACCESS read-only 
		STATUS current
		DESCRIPTION  "Assemble set-cookie fail" 
		::={ acosSlbHttpProxyS 84 } 

		asmSetcookieHeaderFail OBJECT-TYPE
		SYNTAX  CounterBasedGauge64 
		MAX-ACCESS read-only 
		STATUS current
		DESCRIPTION  "Asm set-cookie hdr fail" 
		::={ acosSlbHttpProxyS 85 } 

		clientReqUnexpFlag OBJECT-TYPE
		SYNTAX  CounterBasedGauge64 
		MAX-ACCESS read-only 
		STATUS current
		DESCRIPTION  "Client req unexp flags" 
		::={ acosSlbHttpProxyS 86 } 

		connectingFin OBJECT-TYPE
		SYNTAX  CounterBasedGauge64 
		MAX-ACCESS read-only 
		STATUS current
		DESCRIPTION  "Connecting FIN" 
		::={ acosSlbHttpProxyS 87 } 

		connectingFinRetrans OBJECT-TYPE
		SYNTAX  CounterBasedGauge64 
		MAX-ACCESS read-only 
		STATUS current
		DESCRIPTION  "Connecting FIN retran" 
		::={ acosSlbHttpProxyS 88 } 

		connectingFinOfo OBJECT-TYPE
		SYNTAX  CounterBasedGauge64 
		MAX-ACCESS read-only 
		STATUS current
		DESCRIPTION  "Connecting FIN ofo" 
		::={ acosSlbHttpProxyS 89 } 

		connectingRst OBJECT-TYPE
		SYNTAX  CounterBasedGauge64 
		MAX-ACCESS read-only 
		STATUS current
		DESCRIPTION  "Connecting RST" 
		::={ acosSlbHttpProxyS 90 } 

		connectingRstRetrans OBJECT-TYPE
		SYNTAX  CounterBasedGauge64 
		MAX-ACCESS read-only 
		STATUS current
		DESCRIPTION  "Connecting RST retran" 
		::={ acosSlbHttpProxyS 91 } 

		connectingRstOfo OBJECT-TYPE
		SYNTAX  CounterBasedGauge64 
		MAX-ACCESS read-only 
		STATUS current
		DESCRIPTION  "Connecting RST ofo" 
		::={ acosSlbHttpProxyS 92 } 

		connectingAck OBJECT-TYPE
		SYNTAX  CounterBasedGauge64 
		MAX-ACCESS read-only 
		STATUS current
		DESCRIPTION  "Connecting ACK" 
		::={ acosSlbHttpProxyS 93 } 

		pktsOfo OBJECT-TYPE
		SYNTAX  CounterBasedGauge64 
		MAX-ACCESS read-only 
		STATUS current
		DESCRIPTION  "Packets ofo" 
		::={ acosSlbHttpProxyS 94 } 

		pktsRetrans OBJECT-TYPE
		SYNTAX  CounterBasedGauge64 
		MAX-ACCESS read-only 
		STATUS current
		DESCRIPTION  "Packets retrans" 
		::={ acosSlbHttpProxyS 95 } 

		pktsRetransAckFinwait OBJECT-TYPE
		SYNTAX  CounterBasedGauge64 
		MAX-ACCESS read-only 
		STATUS current
		DESCRIPTION  "retrans ACK FWAIT" 
		::={ acosSlbHttpProxyS 96 } 

		pktsRetransFin OBJECT-TYPE
		SYNTAX  CounterBasedGauge64 
		MAX-ACCESS read-only 
		STATUS current
		DESCRIPTION  "retrans FIN" 
		::={ acosSlbHttpProxyS 97 } 

		pktsRetransRst OBJECT-TYPE
		SYNTAX  CounterBasedGauge64 
		MAX-ACCESS read-only 
		STATUS current
		DESCRIPTION  "retrans RST" 
		::={ acosSlbHttpProxyS 98 } 

		pktsRetransPush OBJECT-TYPE
		SYNTAX  CounterBasedGauge64 
		MAX-ACCESS read-only 
		STATUS current
		DESCRIPTION  "retrans PSH" 
		::={ acosSlbHttpProxyS 99 } 

		staleSess OBJECT-TYPE
		SYNTAX  CounterBasedGauge64 
		MAX-ACCESS read-only 
		STATUS current
		DESCRIPTION  "Stale sess" 
		::={ acosSlbHttpProxyS 100 } 

		serverReselFailed OBJECT-TYPE
		SYNTAX  CounterBasedGauge64 
		MAX-ACCESS read-only 
		STATUS current
		DESCRIPTION  "Server re-select failed" 
		::={ acosSlbHttpProxyS 101 } 

		compressionBefore OBJECT-TYPE
		SYNTAX  CounterBasedGauge64 
		MAX-ACCESS read-only 
		STATUS current
		DESCRIPTION  "Tot data before compress" 
		::={ acosSlbHttpProxyS 102 } 

		compressionAfter OBJECT-TYPE
		SYNTAX  CounterBasedGauge64 
		MAX-ACCESS read-only 
		STATUS current
		DESCRIPTION  "Tot data after compress" 
		::={ acosSlbHttpProxyS 104 } 

		response1xx OBJECT-TYPE
		SYNTAX  CounterBasedGauge64 
		MAX-ACCESS read-only 
		STATUS current
		DESCRIPTION  "Status code 1XX" 
		::={ acosSlbHttpProxyS 106 } 

		response100 OBJECT-TYPE
		SYNTAX  CounterBasedGauge64 
		MAX-ACCESS read-only 
		STATUS current
		DESCRIPTION  "Status code 100" 
		::={ acosSlbHttpProxyS 107 } 

		response101 OBJECT-TYPE
		SYNTAX  CounterBasedGauge64 
		MAX-ACCESS read-only 
		STATUS current
		DESCRIPTION  "Status code 101" 
		::={ acosSlbHttpProxyS 108 } 

		response102 OBJECT-TYPE
		SYNTAX  CounterBasedGauge64 
		MAX-ACCESS read-only 
		STATUS current
		DESCRIPTION  "Status code 102" 
		::={ acosSlbHttpProxyS 109 } 

		response2xx OBJECT-TYPE
		SYNTAX  CounterBasedGauge64 
		MAX-ACCESS read-only 
		STATUS current
		DESCRIPTION  "Status code 2XX" 
		::={ acosSlbHttpProxyS 110 } 

		response200 OBJECT-TYPE
		SYNTAX  CounterBasedGauge64 
		MAX-ACCESS read-only 
		STATUS current
		DESCRIPTION  "Status code 200" 
		::={ acosSlbHttpProxyS 111 } 

		response201 OBJECT-TYPE
		SYNTAX  CounterBasedGauge64 
		MAX-ACCESS read-only 
		STATUS current
		DESCRIPTION  "Status code 201" 
		::={ acosSlbHttpProxyS 112 } 

		response202 OBJECT-TYPE
		SYNTAX  CounterBasedGauge64 
		MAX-ACCESS read-only 
		STATUS current
		DESCRIPTION  "Status code 202" 
		::={ acosSlbHttpProxyS 113 } 

		response203 OBJECT-TYPE
		SYNTAX  CounterBasedGauge64 
		MAX-ACCESS read-only 
		STATUS current
		DESCRIPTION  "Status code 203" 
		::={ acosSlbHttpProxyS 114 } 

		response204 OBJECT-TYPE
		SYNTAX  CounterBasedGauge64 
		MAX-ACCESS read-only 
		STATUS current
		DESCRIPTION  "Status code 204" 
		::={ acosSlbHttpProxyS 115 } 

		response205 OBJECT-TYPE
		SYNTAX  CounterBasedGauge64 
		MAX-ACCESS read-only 
		STATUS current
		DESCRIPTION  "Status code 205" 
		::={ acosSlbHttpProxyS 116 } 

		response206 OBJECT-TYPE
		SYNTAX  CounterBasedGauge64 
		MAX-ACCESS read-only 
		STATUS current
		DESCRIPTION  "Status code 206" 
		::={ acosSlbHttpProxyS 117 } 

		response207 OBJECT-TYPE
		SYNTAX  CounterBasedGauge64 
		MAX-ACCESS read-only 
		STATUS current
		DESCRIPTION  "Status code 207" 
		::={ acosSlbHttpProxyS 118 } 

		response3xx OBJECT-TYPE
		SYNTAX  CounterBasedGauge64 
		MAX-ACCESS read-only 
		STATUS current
		DESCRIPTION  "Status code 3XX" 
		::={ acosSlbHttpProxyS 119 } 

		response300 OBJECT-TYPE
		SYNTAX  CounterBasedGauge64 
		MAX-ACCESS read-only 
		STATUS current
		DESCRIPTION  "Status code 300" 
		::={ acosSlbHttpProxyS 120 } 

		response301 OBJECT-TYPE
		SYNTAX  CounterBasedGauge64 
		MAX-ACCESS read-only 
		STATUS current
		DESCRIPTION  "Status code 301" 
		::={ acosSlbHttpProxyS 121 } 

		response302 OBJECT-TYPE
		SYNTAX  CounterBasedGauge64 
		MAX-ACCESS read-only 
		STATUS current
		DESCRIPTION  "Status code 302" 
		::={ acosSlbHttpProxyS 122 } 

		response303 OBJECT-TYPE
		SYNTAX  CounterBasedGauge64 
		MAX-ACCESS read-only 
		STATUS current
		DESCRIPTION  "Status code 303" 
		::={ acosSlbHttpProxyS 123 } 

		response304 OBJECT-TYPE
		SYNTAX  CounterBasedGauge64 
		MAX-ACCESS read-only 
		STATUS current
		DESCRIPTION  "Status code 304" 
		::={ acosSlbHttpProxyS 124 } 

		response305 OBJECT-TYPE
		SYNTAX  CounterBasedGauge64 
		MAX-ACCESS read-only 
		STATUS current
		DESCRIPTION  "Status code 305" 
		::={ acosSlbHttpProxyS 125 } 

		response306 OBJECT-TYPE
		SYNTAX  CounterBasedGauge64 
		MAX-ACCESS read-only 
		STATUS current
		DESCRIPTION  "Status code 306" 
		::={ acosSlbHttpProxyS 126 } 

		response307 OBJECT-TYPE
		SYNTAX  CounterBasedGauge64 
		MAX-ACCESS read-only 
		STATUS current
		DESCRIPTION  "Status code 307" 
		::={ acosSlbHttpProxyS 127 } 

		response4xx OBJECT-TYPE
		SYNTAX  CounterBasedGauge64 
		MAX-ACCESS read-only 
		STATUS current
		DESCRIPTION  "Status code 4XX" 
		::={ acosSlbHttpProxyS 128 } 

		response400 OBJECT-TYPE
		SYNTAX  CounterBasedGauge64 
		MAX-ACCESS read-only 
		STATUS current
		DESCRIPTION  "Status code 400" 
		::={ acosSlbHttpProxyS 129 } 

		response401 OBJECT-TYPE
		SYNTAX  CounterBasedGauge64 
		MAX-ACCESS read-only 
		STATUS current
		DESCRIPTION  "Status code 401" 
		::={ acosSlbHttpProxyS 130 } 

		response402 OBJECT-TYPE
		SYNTAX  CounterBasedGauge64 
		MAX-ACCESS read-only 
		STATUS current
		DESCRIPTION  "Status code 402" 
		::={ acosSlbHttpProxyS 131 } 

		response403 OBJECT-TYPE
		SYNTAX  CounterBasedGauge64 
		MAX-ACCESS read-only 
		STATUS current
		DESCRIPTION  "Status code 403" 
		::={ acosSlbHttpProxyS 132 } 

		response404 OBJECT-TYPE
		SYNTAX  CounterBasedGauge64 
		MAX-ACCESS read-only 
		STATUS current
		DESCRIPTION  "Status code 404" 
		::={ acosSlbHttpProxyS 133 } 

		response405 OBJECT-TYPE
		SYNTAX  CounterBasedGauge64 
		MAX-ACCESS read-only 
		STATUS current
		DESCRIPTION  "Status code 405" 
		::={ acosSlbHttpProxyS 134 } 

		response406 OBJECT-TYPE
		SYNTAX  CounterBasedGauge64 
		MAX-ACCESS read-only 
		STATUS current
		DESCRIPTION  "Status code 406" 
		::={ acosSlbHttpProxyS 135 } 

		response407 OBJECT-TYPE
		SYNTAX  CounterBasedGauge64 
		MAX-ACCESS read-only 
		STATUS current
		DESCRIPTION  "Status code 407" 
		::={ acosSlbHttpProxyS 136 } 

		response408 OBJECT-TYPE
		SYNTAX  CounterBasedGauge64 
		MAX-ACCESS read-only 
		STATUS current
		DESCRIPTION  "Status code 408" 
		::={ acosSlbHttpProxyS 137 } 

		response409 OBJECT-TYPE
		SYNTAX  CounterBasedGauge64 
		MAX-ACCESS read-only 
		STATUS current
		DESCRIPTION  "Status code 409" 
		::={ acosSlbHttpProxyS 138 } 

		response410 OBJECT-TYPE
		SYNTAX  CounterBasedGauge64 
		MAX-ACCESS read-only 
		STATUS current
		DESCRIPTION  "Status code 410" 
		::={ acosSlbHttpProxyS 139 } 

		response411 OBJECT-TYPE
		SYNTAX  CounterBasedGauge64 
		MAX-ACCESS read-only 
		STATUS current
		DESCRIPTION  "Status code 411" 
		::={ acosSlbHttpProxyS 140 } 

		response412 OBJECT-TYPE
		SYNTAX  CounterBasedGauge64 
		MAX-ACCESS read-only 
		STATUS current
		DESCRIPTION  "Status code 412" 
		::={ acosSlbHttpProxyS 141 } 

		response413 OBJECT-TYPE
		SYNTAX  CounterBasedGauge64 
		MAX-ACCESS read-only 
		STATUS current
		DESCRIPTION  "Status code 413" 
		::={ acosSlbHttpProxyS 142 } 

		response414 OBJECT-TYPE
		SYNTAX  CounterBasedGauge64 
		MAX-ACCESS read-only 
		STATUS current
		DESCRIPTION  "Status code 414" 
		::={ acosSlbHttpProxyS 143 } 

		response415 OBJECT-TYPE
		SYNTAX  CounterBasedGauge64 
		MAX-ACCESS read-only 
		STATUS current
		DESCRIPTION  "Status code 415" 
		::={ acosSlbHttpProxyS 144 } 

		response416 OBJECT-TYPE
		SYNTAX  CounterBasedGauge64 
		MAX-ACCESS read-only 
		STATUS current
		DESCRIPTION  "Status code 416" 
		::={ acosSlbHttpProxyS 145 } 

		response417 OBJECT-TYPE
		SYNTAX  CounterBasedGauge64 
		MAX-ACCESS read-only 
		STATUS current
		DESCRIPTION  "Status code 417" 
		::={ acosSlbHttpProxyS 146 } 

		response418 OBJECT-TYPE
		SYNTAX  CounterBasedGauge64 
		MAX-ACCESS read-only 
		STATUS current
		DESCRIPTION  "Status code 418" 
		::={ acosSlbHttpProxyS 147 } 

		response422 OBJECT-TYPE
		SYNTAX  CounterBasedGauge64 
		MAX-ACCESS read-only 
		STATUS current
		DESCRIPTION  "Status code 422" 
		::={ acosSlbHttpProxyS 148 } 

		response423 OBJECT-TYPE
		SYNTAX  CounterBasedGauge64 
		MAX-ACCESS read-only 
		STATUS current
		DESCRIPTION  "Status code 423" 
		::={ acosSlbHttpProxyS 149 } 

		response424 OBJECT-TYPE
		SYNTAX  CounterBasedGauge64 
		MAX-ACCESS read-only 
		STATUS current
		DESCRIPTION  "Status code 424" 
		::={ acosSlbHttpProxyS 150 } 

		response425 OBJECT-TYPE
		SYNTAX  CounterBasedGauge64 
		MAX-ACCESS read-only 
		STATUS current
		DESCRIPTION  "Status code 425" 
		::={ acosSlbHttpProxyS 151 } 

		response426 OBJECT-TYPE
		SYNTAX  CounterBasedGauge64 
		MAX-ACCESS read-only 
		STATUS current
		DESCRIPTION  "Status code 426" 
		::={ acosSlbHttpProxyS 152 } 

		response449 OBJECT-TYPE
		SYNTAX  CounterBasedGauge64 
		MAX-ACCESS read-only 
		STATUS current
		DESCRIPTION  "Status code 449" 
		::={ acosSlbHttpProxyS 153 } 

		response450 OBJECT-TYPE
		SYNTAX  CounterBasedGauge64 
		MAX-ACCESS read-only 
		STATUS current
		DESCRIPTION  "Status code 450" 
		::={ acosSlbHttpProxyS 154 } 

		response5xx OBJECT-TYPE
		SYNTAX  CounterBasedGauge64 
		MAX-ACCESS read-only 
		STATUS current
		DESCRIPTION  "Status code 5XX" 
		::={ acosSlbHttpProxyS 155 } 

		response500 OBJECT-TYPE
		SYNTAX  CounterBasedGauge64 
		MAX-ACCESS read-only 
		STATUS current
		DESCRIPTION  "Status code 500" 
		::={ acosSlbHttpProxyS 156 } 

		response501 OBJECT-TYPE
		SYNTAX  CounterBasedGauge64 
		MAX-ACCESS read-only 
		STATUS current
		DESCRIPTION  "Status code 501" 
		::={ acosSlbHttpProxyS 157 } 

		response502 OBJECT-TYPE
		SYNTAX  CounterBasedGauge64 
		MAX-ACCESS read-only 
		STATUS current
		DESCRIPTION  "Status code 502" 
		::={ acosSlbHttpProxyS 158 } 

		response503 OBJECT-TYPE
		SYNTAX  CounterBasedGauge64 
		MAX-ACCESS read-only 
		STATUS current
		DESCRIPTION  "Status code 503" 
		::={ acosSlbHttpProxyS 159 } 

		response504 OBJECT-TYPE
		SYNTAX  CounterBasedGauge64 
		MAX-ACCESS read-only 
		STATUS current
		DESCRIPTION  "Status code 504" 
		::={ acosSlbHttpProxyS 160 } 

		response505 OBJECT-TYPE
		SYNTAX  CounterBasedGauge64 
		MAX-ACCESS read-only 
		STATUS current
		DESCRIPTION  "Status code 505" 
		::={ acosSlbHttpProxyS 161 } 

		response506 OBJECT-TYPE
		SYNTAX  CounterBasedGauge64 
		MAX-ACCESS read-only 
		STATUS current
		DESCRIPTION  "Status code 506" 
		::={ acosSlbHttpProxyS 162 } 

		response507 OBJECT-TYPE
		SYNTAX  CounterBasedGauge64 
		MAX-ACCESS read-only 
		STATUS current
		DESCRIPTION  "Status code 507" 
		::={ acosSlbHttpProxyS 163 } 

		response508 OBJECT-TYPE
		SYNTAX  CounterBasedGauge64 
		MAX-ACCESS read-only 
		STATUS current
		DESCRIPTION  "Status code 508" 
		::={ acosSlbHttpProxyS 164 } 

		response509 OBJECT-TYPE
		SYNTAX  CounterBasedGauge64 
		MAX-ACCESS read-only 
		STATUS current
		DESCRIPTION  "Status code 509" 
		::={ acosSlbHttpProxyS 165 } 

		response510 OBJECT-TYPE
		SYNTAX  CounterBasedGauge64 
		MAX-ACCESS read-only 
		STATUS current
		DESCRIPTION  "Status code 510" 
		::={ acosSlbHttpProxyS 166 } 

		response6xx OBJECT-TYPE
		SYNTAX  CounterBasedGauge64 
		MAX-ACCESS read-only 
		STATUS current
		DESCRIPTION  "Status code 6XX" 
		::={ acosSlbHttpProxyS 167 } 

		responseUnknown OBJECT-TYPE
		SYNTAX  CounterBasedGauge64 
		MAX-ACCESS read-only 
		STATUS current
		DESCRIPTION  "Status code unknown" 
		::={ acosSlbHttpProxyS 168 } 

		reqHttp10 OBJECT-TYPE
		SYNTAX  CounterBasedGauge64 
		MAX-ACCESS read-only 
		STATUS current
		DESCRIPTION  "Request 1.0" 
		::={ acosSlbHttpProxyS 169 } 

		reqHttp11 OBJECT-TYPE
		SYNTAX  CounterBasedGauge64 
		MAX-ACCESS read-only 
		STATUS current
		DESCRIPTION  "Request 1.1" 
		::={ acosSlbHttpProxyS 170 } 

		responseHttp10 OBJECT-TYPE
		SYNTAX  CounterBasedGauge64 
		MAX-ACCESS read-only 
		STATUS current
		DESCRIPTION  "Resp 1.0" 
		::={ acosSlbHttpProxyS 171 } 

		responseHttp11 OBJECT-TYPE
		SYNTAX  CounterBasedGauge64 
		MAX-ACCESS read-only 
		STATUS current
		DESCRIPTION  "Resp 1.1" 
		::={ acosSlbHttpProxyS 172 } 

		reqGet OBJECT-TYPE
		SYNTAX  CounterBasedGauge64 
		MAX-ACCESS read-only 
		STATUS current
		DESCRIPTION  "Method GET" 
		::={ acosSlbHttpProxyS 173 } 

		reqHead OBJECT-TYPE
		SYNTAX  CounterBasedGauge64 
		MAX-ACCESS read-only 
		STATUS current
		DESCRIPTION  "Method HEAD" 
		::={ acosSlbHttpProxyS 174 } 

		reqPut OBJECT-TYPE
		SYNTAX  CounterBasedGauge64 
		MAX-ACCESS read-only 
		STATUS current
		DESCRIPTION  "Method PUT" 
		::={ acosSlbHttpProxyS 175 } 

		reqPost OBJECT-TYPE
		SYNTAX  CounterBasedGauge64 
		MAX-ACCESS read-only 
		STATUS current
		DESCRIPTION  "Method POST" 
		::={ acosSlbHttpProxyS 176 } 

		reqTrace OBJECT-TYPE
		SYNTAX  CounterBasedGauge64 
		MAX-ACCESS read-only 
		STATUS current
		DESCRIPTION  "Method TRACE" 
		::={ acosSlbHttpProxyS 177 } 

		reqOptions OBJECT-TYPE
		SYNTAX  CounterBasedGauge64 
		MAX-ACCESS read-only 
		STATUS current
		DESCRIPTION  "Method OPTIONS" 
		::={ acosSlbHttpProxyS 178 } 

		reqConnect OBJECT-TYPE
		SYNTAX  CounterBasedGauge64 
		MAX-ACCESS read-only 
		STATUS current
		DESCRIPTION  "Method CONNECT" 
		::={ acosSlbHttpProxyS 179 } 

		reqDelete OBJECT-TYPE
		SYNTAX  CounterBasedGauge64 
		MAX-ACCESS read-only 
		STATUS current
		DESCRIPTION  "Method DELETE" 
		::={ acosSlbHttpProxyS 180 } 

		reqUnknown OBJECT-TYPE
		SYNTAX  CounterBasedGauge64 
		MAX-ACCESS read-only 
		STATUS current
		DESCRIPTION  "Method UNKNOWN" 
		::={ acosSlbHttpProxyS 181 } 

		reqContentLen OBJECT-TYPE
		SYNTAX  CounterBasedGauge64 
		MAX-ACCESS read-only 
		STATUS current
		DESCRIPTION  "Req content len" 
		::={ acosSlbHttpProxyS 182 } 

		rspContentLen OBJECT-TYPE
		SYNTAX  CounterBasedGauge64 
		MAX-ACCESS read-only 
		STATUS current
		DESCRIPTION  "Resp content len" 
		::={ acosSlbHttpProxyS 183 } 

		rspChunk OBJECT-TYPE
		SYNTAX  CounterBasedGauge64 
		MAX-ACCESS read-only 
		STATUS current
		DESCRIPTION  "Resp chunk encoding" 
		::={ acosSlbHttpProxyS 184 } 

		reqChunk OBJECT-TYPE
		SYNTAX  CounterBasedGauge64 
		MAX-ACCESS read-only 
		STATUS current
		DESCRIPTION  "Req chunk encoding" 
		::={ acosSlbHttpProxyS 185 } 

		compressRsp OBJECT-TYPE
		SYNTAX  CounterBasedGauge64 
		MAX-ACCESS read-only 
		STATUS current
		DESCRIPTION  "Compress req" 
		::={ acosSlbHttpProxyS 186 } 

		compressDelAcceptEnc OBJECT-TYPE
		SYNTAX  CounterBasedGauge64 
		MAX-ACCESS read-only 
		STATUS current
		DESCRIPTION  "Compress del accept enc" 
		::={ acosSlbHttpProxyS 187 } 

		compressRespAlreadyCompressed OBJECT-TYPE
		SYNTAX  CounterBasedGauge64 
		MAX-ACCESS read-only 
		STATUS current
		DESCRIPTION  "Resp already compressed" 
		::={ acosSlbHttpProxyS 188 } 

		compressContentTypeExcluded OBJECT-TYPE
		SYNTAX  CounterBasedGauge64 
		MAX-ACCESS read-only 
		STATUS current
		DESCRIPTION  "Compress cont type excl" 
		::={ acosSlbHttpProxyS 189 } 

		compressNoContentType OBJECT-TYPE
		SYNTAX  CounterBasedGauge64 
		MAX-ACCESS read-only 
		STATUS current
		DESCRIPTION  "Compress no cont type" 
		::={ acosSlbHttpProxyS 190 } 

		compressRespLtMin OBJECT-TYPE
		SYNTAX  CounterBasedGauge64 
		MAX-ACCESS read-only 
		STATUS current
		DESCRIPTION  "Compress resp less than min" 
		::={ acosSlbHttpProxyS 191 } 

		compressRespNoClOrCe OBJECT-TYPE
		SYNTAX  CounterBasedGauge64 
		MAX-ACCESS read-only 
		STATUS current
		DESCRIPTION  "Compress resp no CL/CE" 
		::={ acosSlbHttpProxyS 192 } 

		compressRatioTooHigh OBJECT-TYPE
		SYNTAX  CounterBasedGauge64 
		MAX-ACCESS read-only 
		STATUS current
		DESCRIPTION  "Compress ratio too high" 
		::={ acosSlbHttpProxyS 193 } 

		cacheRsp OBJECT-TYPE
		SYNTAX  CounterBasedGauge64 
		MAX-ACCESS read-only 
		STATUS current
		DESCRIPTION  "HTTP req (cache succ)" 
		::={ acosSlbHttpProxyS 194 } 

		slbHttpProxyCloseOnDdos OBJECT-TYPE
		SYNTAX  CounterBasedGauge64 
		MAX-ACCESS read-only 
		STATUS current
		DESCRIPTION  "Close on DDoS" 
		::={ acosSlbHttpProxyS 195 } 

		reqHttp10Keepalive OBJECT-TYPE
		SYNTAX  CounterBasedGauge64 
		MAX-ACCESS read-only 
		STATUS current
		DESCRIPTION  "1.0 Keepalive" 
		::={ acosSlbHttpProxyS 196 } 

		reqSz1k OBJECT-TYPE
		SYNTAX  CounterBasedGauge64 
		MAX-ACCESS read-only 
		STATUS current
		DESCRIPTION  "Req less than equal to 1K" 
		::={ acosSlbHttpProxyS 197 } 

		reqSz2k OBJECT-TYPE
		SYNTAX  CounterBasedGauge64 
		MAX-ACCESS read-only 
		STATUS current
		DESCRIPTION  "Req less than equal to 2K" 
		::={ acosSlbHttpProxyS 198 } 

		reqSz4k OBJECT-TYPE
		SYNTAX  CounterBasedGauge64 
		MAX-ACCESS read-only 
		STATUS current
		DESCRIPTION  "Req less than equal to 4K" 
		::={ acosSlbHttpProxyS 199 } 

		reqSz8k OBJECT-TYPE
		SYNTAX  CounterBasedGauge64 
		MAX-ACCESS read-only 
		STATUS current
		DESCRIPTION  "Req less than equal to 8K" 
		::={ acosSlbHttpProxyS 200 } 

		reqSz16k OBJECT-TYPE
		SYNTAX  CounterBasedGauge64 
		MAX-ACCESS read-only 
		STATUS current
		DESCRIPTION  "Req less than equal to 16K" 
		::={ acosSlbHttpProxyS 201 } 

		reqSz32k OBJECT-TYPE
		SYNTAX  CounterBasedGauge64 
		MAX-ACCESS read-only 
		STATUS current
		DESCRIPTION  "Req less than equal to 32K" 
		::={ acosSlbHttpProxyS 202 } 

		reqSz64k OBJECT-TYPE
		SYNTAX  CounterBasedGauge64 
		MAX-ACCESS read-only 
		STATUS current
		DESCRIPTION  "Req less than equal to 64K" 
		::={ acosSlbHttpProxyS 203 } 

		reqSz256k OBJECT-TYPE
		SYNTAX  CounterBasedGauge64 
		MAX-ACCESS read-only 
		STATUS current
		DESCRIPTION  "Req less than equal to 256K" 
		::={ acosSlbHttpProxyS 204 } 

		reqSzGt256k OBJECT-TYPE
		SYNTAX  CounterBasedGauge64 
		MAX-ACCESS read-only 
		STATUS current
		DESCRIPTION  "Req greater than 256K" 
		::={ acosSlbHttpProxyS 205 } 

		rspSz1k OBJECT-TYPE
		SYNTAX  CounterBasedGauge64 
		MAX-ACCESS read-only 
		STATUS current
		DESCRIPTION  "Resp less than equal to 1K" 
		::={ acosSlbHttpProxyS 206 } 

		rspSz2k OBJECT-TYPE
		SYNTAX  CounterBasedGauge64 
		MAX-ACCESS read-only 
		STATUS current
		DESCRIPTION  "Resp less than equal to 2K" 
		::={ acosSlbHttpProxyS 207 } 

		rspSz4k OBJECT-TYPE
		SYNTAX  CounterBasedGauge64 
		MAX-ACCESS read-only 
		STATUS current
		DESCRIPTION  "Resp less than equal to 4K" 
		::={ acosSlbHttpProxyS 208 } 

		rspSz8k OBJECT-TYPE
		SYNTAX  CounterBasedGauge64 
		MAX-ACCESS read-only 
		STATUS current
		DESCRIPTION  "Resp less than equal to 8K" 
		::={ acosSlbHttpProxyS 209 } 

		rspSz16k OBJECT-TYPE
		SYNTAX  CounterBasedGauge64 
		MAX-ACCESS read-only 
		STATUS current
		DESCRIPTION  "Resp less than equal to 16K" 
		::={ acosSlbHttpProxyS 210 } 

		rspSz32k OBJECT-TYPE
		SYNTAX  CounterBasedGauge64 
		MAX-ACCESS read-only 
		STATUS current
		DESCRIPTION  "Resp less than equal to 32K" 
		::={ acosSlbHttpProxyS 211 } 

		rspSz64k OBJECT-TYPE
		SYNTAX  CounterBasedGauge64 
		MAX-ACCESS read-only 
		STATUS current
		DESCRIPTION  "Resp less than equal to 64K" 
		::={ acosSlbHttpProxyS 212 } 

		rspSz256k OBJECT-TYPE
		SYNTAX  CounterBasedGauge64 
		MAX-ACCESS read-only 
		STATUS current
		DESCRIPTION  "Resp less than equal to 256K" 
		::={ acosSlbHttpProxyS 213 } 

		rspSzGt256k OBJECT-TYPE
		SYNTAX  CounterBasedGauge64 
		MAX-ACCESS read-only 
		STATUS current
		DESCRIPTION  "Resp greater than 256K" 
		::={ acosSlbHttpProxyS 214 } 

		chunkSz512 OBJECT-TYPE
		SYNTAX  CounterBasedGauge64 
		MAX-ACCESS read-only 
		STATUS current
		DESCRIPTION  "Chunk less than equal to 512" 
		::={ acosSlbHttpProxyS 215 } 

		chunkSz1k OBJECT-TYPE
		SYNTAX  CounterBasedGauge64 
		MAX-ACCESS read-only 
		STATUS current
		DESCRIPTION  "Chunk less than equal to 1K" 
		::={ acosSlbHttpProxyS 216 } 

		chunkSz2k OBJECT-TYPE
		SYNTAX  CounterBasedGauge64 
		MAX-ACCESS read-only 
		STATUS current
		DESCRIPTION  "Chunk less than equal to 2K" 
		::={ acosSlbHttpProxyS 217 } 

		chunkSz4k OBJECT-TYPE
		SYNTAX  CounterBasedGauge64 
		MAX-ACCESS read-only 
		STATUS current
		DESCRIPTION  "Chunk less than equal to 4K" 
		::={ acosSlbHttpProxyS 218 } 

		chunkSzGt4k OBJECT-TYPE
		SYNTAX  CounterBasedGauge64 
		MAX-ACCESS read-only 
		STATUS current
		DESCRIPTION  "Chunk greater than 4K" 
		::={ acosSlbHttpProxyS 219 } 

		pconnConnecting OBJECT-TYPE
		SYNTAX  CounterBasedGauge64 
		MAX-ACCESS read-only 
		STATUS current
		DESCRIPTION  "pconn connecting" 
		::={ acosSlbHttpProxyS 220 } 

		pconnConnected OBJECT-TYPE
		SYNTAX  CounterBasedGauge64 
		MAX-ACCESS read-only 
		STATUS current
		DESCRIPTION  "pconn connected" 
		::={ acosSlbHttpProxyS 221 } 

		pconnConnectingFailed OBJECT-TYPE
		SYNTAX  CounterBasedGauge64 
		MAX-ACCESS read-only 
		STATUS current
		DESCRIPTION  "pconn conn failed" 
		::={ acosSlbHttpProxyS 222 } 

		chunkBad OBJECT-TYPE
		SYNTAX  CounterBasedGauge64 
		MAX-ACCESS read-only 
		STATUS current
		DESCRIPTION  "Bad Chunk" 
		::={ acosSlbHttpProxyS 223 } 

		req10u OBJECT-TYPE
		SYNTAX  CounterBasedGauge64 
		MAX-ACCESS read-only 
		STATUS current
		DESCRIPTION  "Rsp time less than 10u" 
		::={ acosSlbHttpProxyS 238 } 

		req20u OBJECT-TYPE
		SYNTAX  CounterBasedGauge64 
		MAX-ACCESS read-only 
		STATUS current
		DESCRIPTION  "Rsp time less than 20u" 
		::={ acosSlbHttpProxyS 239 } 

		req50u OBJECT-TYPE
		SYNTAX  CounterBasedGauge64 
		MAX-ACCESS read-only 
		STATUS current
		DESCRIPTION  "Rsp time less than 50u" 
		::={ acosSlbHttpProxyS 240 } 

		req100u OBJECT-TYPE
		SYNTAX  CounterBasedGauge64 
		MAX-ACCESS read-only 
		STATUS current
		DESCRIPTION  "Rsp time less than 100u" 
		::={ acosSlbHttpProxyS 241 } 

		req200u OBJECT-TYPE
		SYNTAX  CounterBasedGauge64 
		MAX-ACCESS read-only 
		STATUS current
		DESCRIPTION  "Rsp time less than 200u" 
		::={ acosSlbHttpProxyS 242 } 

		req500u OBJECT-TYPE
		SYNTAX  CounterBasedGauge64 
		MAX-ACCESS read-only 
		STATUS current
		DESCRIPTION  "Rsp time less than 500u" 
		::={ acosSlbHttpProxyS 243 } 

		req1m OBJECT-TYPE
		SYNTAX  CounterBasedGauge64 
		MAX-ACCESS read-only 
		STATUS current
		DESCRIPTION  "Rsp time less than 1m" 
		::={ acosSlbHttpProxyS 244 } 

		req2m OBJECT-TYPE
		SYNTAX  CounterBasedGauge64 
		MAX-ACCESS read-only 
		STATUS current
		DESCRIPTION  "Rsp time less than 2m" 
		::={ acosSlbHttpProxyS 245 } 

		req5m OBJECT-TYPE
		SYNTAX  CounterBasedGauge64 
		MAX-ACCESS read-only 
		STATUS current
		DESCRIPTION  "Rsp time less than 5m" 
		::={ acosSlbHttpProxyS 246 } 

		req10m OBJECT-TYPE
		SYNTAX  CounterBasedGauge64 
		MAX-ACCESS read-only 
		STATUS current
		DESCRIPTION  "Rsp time less than 10m" 
		::={ acosSlbHttpProxyS 247 } 

		req20m OBJECT-TYPE
		SYNTAX  CounterBasedGauge64 
		MAX-ACCESS read-only 
		STATUS current
		DESCRIPTION  "Rsp time less than 20m" 
		::={ acosSlbHttpProxyS 248 } 

		req50m OBJECT-TYPE
		SYNTAX  CounterBasedGauge64 
		MAX-ACCESS read-only 
		STATUS current
		DESCRIPTION  "Rsp time less than 50m" 
		::={ acosSlbHttpProxyS 249 } 

		req100m OBJECT-TYPE
		SYNTAX  CounterBasedGauge64 
		MAX-ACCESS read-only 
		STATUS current
		DESCRIPTION  "Rsp time less than 100m" 
		::={ acosSlbHttpProxyS 250 } 

		req200m OBJECT-TYPE
		SYNTAX  CounterBasedGauge64 
		MAX-ACCESS read-only 
		STATUS current
		DESCRIPTION  "Rsp time less than 200m" 
		::={ acosSlbHttpProxyS 251 } 

		req500m OBJECT-TYPE
		SYNTAX  CounterBasedGauge64 
		MAX-ACCESS read-only 
		STATUS current
		DESCRIPTION  "Rsp time less than 500m" 
		::={ acosSlbHttpProxyS 252 } 

		req1s OBJECT-TYPE
		SYNTAX  CounterBasedGauge64 
		MAX-ACCESS read-only 
		STATUS current
		DESCRIPTION  "Rsp time less than 1s" 
		::={ acosSlbHttpProxyS 253 } 

		req2s OBJECT-TYPE
		SYNTAX  CounterBasedGauge64 
		MAX-ACCESS read-only 
		STATUS current
		DESCRIPTION  "Rsp time less than 2s" 
		::={ acosSlbHttpProxyS 254 } 

		req5s OBJECT-TYPE
		SYNTAX  CounterBasedGauge64 
		MAX-ACCESS read-only 
		STATUS current
		DESCRIPTION  "Rsp time less than 5s" 
		::={ acosSlbHttpProxyS 255 } 

		reqOver5s OBJECT-TYPE
		SYNTAX  CounterBasedGauge64 
		MAX-ACCESS read-only 
		STATUS current
		DESCRIPTION  "Rsp time greater than equal to 5s" 
		::={ acosSlbHttpProxyS 256 } 

		insertClientPort OBJECT-TYPE
		SYNTAX  CounterBasedGauge64 
		MAX-ACCESS read-only 
		STATUS current
		DESCRIPTION  "Insert client Port" 
		::={ acosSlbHttpProxyS 257 } 

		reqTrack OBJECT-TYPE
		SYNTAX  CounterBasedGauge64 
		MAX-ACCESS read-only 
		STATUS current
		DESCRIPTION  "Method TRACK" 
		::={ acosSlbHttpProxyS 258 } 

		connectReq OBJECT-TYPE
		SYNTAX  CounterBasedGauge64 
		MAX-ACCESS read-only 
		STATUS current
		DESCRIPTION  "Total HTTP CONNECT requests" 
		::={ acosSlbHttpProxyS 259 } 

		reqEnterSsli OBJECT-TYPE
		SYNTAX  CounterBasedGauge64 
		MAX-ACCESS read-only 
		STATUS current
		DESCRIPTION  "Total HTTP requests enter SSLi" 
		::={ acosSlbHttpProxyS 260 } 

		nonHttpBypass OBJECT-TYPE
		SYNTAX  CounterBasedGauge64 
		MAX-ACCESS read-only 
		STATUS current
		DESCRIPTION  "Non-HTTP bypass" 
		::={ acosSlbHttpProxyS 261 } 

		decompressionBefore OBJECT-TYPE
		SYNTAX  CounterBasedGauge64 
		MAX-ACCESS read-only 
		STATUS current
		DESCRIPTION  "Tot data before decompress" 
		::={ acosSlbHttpProxyS 263 } 

		decompressionAfter OBJECT-TYPE
		SYNTAX  CounterBasedGauge64 
		MAX-ACCESS read-only 
		STATUS current
		DESCRIPTION  "Tot data after decompress" 
		::={ acosSlbHttpProxyS 264 } 

		reqHttp2 OBJECT-TYPE
		SYNTAX  CounterBasedGauge64 
		MAX-ACCESS read-only 
		STATUS current
		DESCRIPTION  "Request 2.0" 
		::={ acosSlbHttpProxyS 265 } 

		responseHttp2 OBJECT-TYPE
		SYNTAX  CounterBasedGauge64 
		MAX-ACCESS read-only 
		STATUS current
		DESCRIPTION  "Resp 2.0" 
		::={ acosSlbHttpProxyS 266 } 

		reqTimeoutRetry OBJECT-TYPE
		SYNTAX  CounterBasedGauge64 
		MAX-ACCESS read-only 
		STATUS current
		DESCRIPTION  "Retry on Req Timeout" 
		::={ acosSlbHttpProxyS 267 } 

		reqTimeoutClose OBJECT-TYPE
		SYNTAX  CounterBasedGauge64 
		MAX-ACCESS read-only 
		STATUS current
		DESCRIPTION  "Close on Req Timeout" 
		::={ acosSlbHttpProxyS 268 } 

		dohReq OBJECT-TYPE
		SYNTAX  CounterBasedGauge64 
		MAX-ACCESS read-only 
		STATUS current
		DESCRIPTION  "DoH Requests" 
		::={ acosSlbHttpProxyS 269 } 

		dohReqGet OBJECT-TYPE
		SYNTAX  CounterBasedGauge64 
		MAX-ACCESS read-only 
		STATUS current
		DESCRIPTION  "DoH GET Requests" 
		::={ acosSlbHttpProxyS 270 } 

		dohReqPost OBJECT-TYPE
		SYNTAX  CounterBasedGauge64 
		MAX-ACCESS read-only 
		STATUS current
		DESCRIPTION  "DoH POST Requests" 
		::={ acosSlbHttpProxyS 271 } 

		dohNonDohReq OBJECT-TYPE
		SYNTAX  CounterBasedGauge64 
		MAX-ACCESS read-only 
		STATUS current
		DESCRIPTION  "DoH non DoH Requests" 
		::={ acosSlbHttpProxyS 272 } 

		dohNonDohReqGet OBJECT-TYPE
		SYNTAX  CounterBasedGauge64 
		MAX-ACCESS read-only 
		STATUS current
		DESCRIPTION  "DoH non DoH GET Requests" 
		::={ acosSlbHttpProxyS 273 } 

		dohNonDohReqPost OBJECT-TYPE
		SYNTAX  CounterBasedGauge64 
		MAX-ACCESS read-only 
		STATUS current
		DESCRIPTION  "DoH non DoH POST Requests" 
		::={ acosSlbHttpProxyS 274 } 

		dohResp OBJECT-TYPE
		SYNTAX  CounterBasedGauge64 
		MAX-ACCESS read-only 
		STATUS current
		DESCRIPTION  "DoH Responses" 
		::={ acosSlbHttpProxyS 275 } 

		dohTcResp OBJECT-TYPE
		SYNTAX  CounterBasedGauge64 
		MAX-ACCESS read-only 
		STATUS current
		DESCRIPTION  "DoH TC Responses" 
		::={ acosSlbHttpProxyS 276 } 

		dohUdpDnsReq OBJECT-TYPE
		SYNTAX  CounterBasedGauge64 
		MAX-ACCESS read-only 
		STATUS current
		DESCRIPTION  "DoH UDP DNS Requests" 
		::={ acosSlbHttpProxyS 277 } 

		dohUdpDnsResp OBJECT-TYPE
		SYNTAX  CounterBasedGauge64 
		MAX-ACCESS read-only 
		STATUS current
		DESCRIPTION  "DoH UDP DNS Responses" 
		::={ acosSlbHttpProxyS 278 } 

		dohTcpDnsReq OBJECT-TYPE
		SYNTAX  CounterBasedGauge64 
		MAX-ACCESS read-only 
		STATUS current
		DESCRIPTION  "DoH TCP DNS Requests" 
		::={ acosSlbHttpProxyS 279 } 

		dohTcpDnsResp OBJECT-TYPE
		SYNTAX  CounterBasedGauge64 
		MAX-ACCESS read-only 
		STATUS current
		DESCRIPTION  "DoH TCP DNS Responses" 
		::={ acosSlbHttpProxyS 280 } 

		dohReqSendFailed OBJECT-TYPE
		SYNTAX  CounterBasedGauge64 
		MAX-ACCESS read-only 
		STATUS current
		DESCRIPTION  "DoH Request Send Failed" 
		::={ acosSlbHttpProxyS 281 } 

		dohRespSendFailed OBJECT-TYPE
		SYNTAX  CounterBasedGauge64 
		MAX-ACCESS read-only 
		STATUS current
		DESCRIPTION  "DoH Response Send Failed" 
		::={ acosSlbHttpProxyS 282 } 

		dohMallocFail OBJECT-TYPE
		SYNTAX  CounterBasedGauge64 
		MAX-ACCESS read-only 
		STATUS current
		DESCRIPTION  "DoH Memory alloc failed" 
		::={ acosSlbHttpProxyS 283 } 

		dohReqUdpRetry OBJECT-TYPE
		SYNTAX  CounterBasedGauge64 
		MAX-ACCESS read-only 
		STATUS current
		DESCRIPTION  "DoH UDP Retry" 
		::={ acosSlbHttpProxyS 284 } 

		dohReqUdpRetryFail OBJECT-TYPE
		SYNTAX  CounterBasedGauge64 
		MAX-ACCESS read-only 
		STATUS current
		DESCRIPTION  "DoH UDP Retry failed" 
		::={ acosSlbHttpProxyS 285 } 

		dohReqTcpRetry OBJECT-TYPE
		SYNTAX  CounterBasedGauge64 
		MAX-ACCESS read-only 
		STATUS current
		DESCRIPTION  "DoH TCP Retry" 
		::={ acosSlbHttpProxyS 286 } 

		dohReqTcpRetryFail OBJECT-TYPE
		SYNTAX  CounterBasedGauge64 
		MAX-ACCESS read-only 
		STATUS current
		DESCRIPTION  "DoH TCP Retry failed" 
		::={ acosSlbHttpProxyS 287 } 

		dohSnatFailed OBJECT-TYPE
		SYNTAX  CounterBasedGauge64 
		MAX-ACCESS read-only 
		STATUS current
		DESCRIPTION  "DoH Source NAT failed" 
		::={ acosSlbHttpProxyS 288 } 

		dohPathNotFound OBJECT-TYPE
		SYNTAX  CounterBasedGauge64 
		MAX-ACCESS read-only 
		STATUS current
		DESCRIPTION  "DoH URI Path not found" 
		::={ acosSlbHttpProxyS 289 } 

		dohGetDnsArgFailed OBJECT-TYPE
		SYNTAX  CounterBasedGauge64 
		MAX-ACCESS read-only 
		STATUS current
		DESCRIPTION  "DoH GET dns arg not found in uri" 
		::={ acosSlbHttpProxyS 290 } 

		dohGetBase64DecodeFailed OBJECT-TYPE
		SYNTAX  CounterBasedGauge64 
		MAX-ACCESS read-only 
		STATUS current
		DESCRIPTION  "DoH GET base64url decode failed" 
		::={ acosSlbHttpProxyS 291 } 

		dohPostContentTypeMismatch OBJECT-TYPE
		SYNTAX  CounterBasedGauge64 
		MAX-ACCESS read-only 
		STATUS current
		DESCRIPTION  "DoH POST content-type not found" 
		::={ acosSlbHttpProxyS 292 } 

		dohPostPayloadNotFound OBJECT-TYPE
		SYNTAX  CounterBasedGauge64 
		MAX-ACCESS read-only 
		STATUS current
		DESCRIPTION  "DoH POST payload not found" 
		::={ acosSlbHttpProxyS 293 } 

		dohPostPayloadExtractFailed OBJECT-TYPE
		SYNTAX  CounterBasedGauge64 
		MAX-ACCESS read-only 
		STATUS current
		DESCRIPTION  "DoH POST payload extract failed" 
		::={ acosSlbHttpProxyS 294 } 

		dohNonDohMethod OBJECT-TYPE
		SYNTAX  CounterBasedGauge64 
		MAX-ACCESS read-only 
		STATUS current
		DESCRIPTION  "DoH Non DoH HTTP request method rcvd" 
		::={ acosSlbHttpProxyS 295 } 

		dohTcpSendFailed OBJECT-TYPE
		SYNTAX  CounterBasedGauge64 
		MAX-ACCESS read-only 
		STATUS current
		DESCRIPTION  "DoH serv TCP DNS send failed" 
		::={ acosSlbHttpProxyS 296 } 

		dohUdpSendFailed OBJECT-TYPE
		SYNTAX  CounterBasedGauge64 
		MAX-ACCESS read-only 
		STATUS current
		DESCRIPTION  "DoH serv UDP DNS send failed" 
		::={ acosSlbHttpProxyS 297 } 

		dohQueryTimeOut OBJECT-TYPE
		SYNTAX  CounterBasedGauge64 
		MAX-ACCESS read-only 
		STATUS current
		DESCRIPTION  "DoH serv Query timed out" 
		::={ acosSlbHttpProxyS 298 } 

		dohDnsQueryTypeA OBJECT-TYPE
		SYNTAX  CounterBasedGauge64 
		MAX-ACCESS read-only 
		STATUS current
		DESCRIPTION  "DoH Query type A" 
		::={ acosSlbHttpProxyS 299 } 

		dohDnsQueryTypeAaaa OBJECT-TYPE
		SYNTAX  CounterBasedGauge64 
		MAX-ACCESS read-only 
		STATUS current
		DESCRIPTION  "DoH Query type AAAA" 
		::={ acosSlbHttpProxyS 300 } 

		dohDnsQueryTypeNs OBJECT-TYPE
		SYNTAX  CounterBasedGauge64 
		MAX-ACCESS read-only 
		STATUS current
		DESCRIPTION  "DoH Query type NS" 
		::={ acosSlbHttpProxyS 301 } 

		dohDnsQueryTypeCname OBJECT-TYPE
		SYNTAX  CounterBasedGauge64 
		MAX-ACCESS read-only 
		STATUS current
		DESCRIPTION  "DoH Query type CNAME" 
		::={ acosSlbHttpProxyS 302 } 

		dohDnsQueryTypeAny OBJECT-TYPE
		SYNTAX  CounterBasedGauge64 
		MAX-ACCESS read-only 
		STATUS current
		DESCRIPTION  "DoH Query type ANY" 
		::={ acosSlbHttpProxyS 303 } 

		dohDnsQueryTypeSrv OBJECT-TYPE
		SYNTAX  CounterBasedGauge64 
		MAX-ACCESS read-only 
		STATUS current
		DESCRIPTION  "DoH Query type SRV" 
		::={ acosSlbHttpProxyS 304 } 

		dohDnsQueryTypeMx OBJECT-TYPE
		SYNTAX  CounterBasedGauge64 
		MAX-ACCESS read-only 
		STATUS current
		DESCRIPTION  "DoH Query type MX" 
		::={ acosSlbHttpProxyS 305 } 

		dohDnsQueryTypeSoa OBJECT-TYPE
		SYNTAX  CounterBasedGauge64 
		MAX-ACCESS read-only 
		STATUS current
		DESCRIPTION  "DoH Query type SOA" 
		::={ acosSlbHttpProxyS 306 } 

		dohDnsQueryTypeOthers OBJECT-TYPE
		SYNTAX  CounterBasedGauge64 
		MAX-ACCESS read-only 
		STATUS current
		DESCRIPTION  "DoH Query type Others" 
		::={ acosSlbHttpProxyS 307 } 

		dohRespSetupFailed OBJECT-TYPE
		SYNTAX  CounterBasedGauge64 
		MAX-ACCESS read-only 
		STATUS current
		DESCRIPTION  "DoH Response setup failed" 
		::={ acosSlbHttpProxyS 308 } 

		dohRespHeaderAllocFailed OBJECT-TYPE
		SYNTAX  CounterBasedGauge64 
		MAX-ACCESS read-only 
		STATUS current
		DESCRIPTION  "DoH Resp hdr alloc failed" 
		::={ acosSlbHttpProxyS 309 } 

		dohRespQueFailed OBJECT-TYPE
		SYNTAX  CounterBasedGauge64 
		MAX-ACCESS read-only 
		STATUS current
		DESCRIPTION  "DoH Resp queue failed" 
		::={ acosSlbHttpProxyS 310 } 

		dohRespUdpFrags OBJECT-TYPE
		SYNTAX  CounterBasedGauge64 
		MAX-ACCESS read-only 
		STATUS current
		DESCRIPTION  "DoH UDP Frags Rcvd" 
		::={ acosSlbHttpProxyS 311 } 

		dohRespTcpFrags OBJECT-TYPE
		SYNTAX  CounterBasedGauge64 
		MAX-ACCESS read-only 
		STATUS current
		DESCRIPTION  "DoH TCP Frags Rcvd" 
		::={ acosSlbHttpProxyS 312 } 

		dohServSelFailed OBJECT-TYPE
		SYNTAX  CounterBasedGauge64 
		MAX-ACCESS read-only 
		STATUS current
		DESCRIPTION  "DoH Server Select Failed" 
		::={ acosSlbHttpProxyS 313 } 

		dohRetryWTcp OBJECT-TYPE
		SYNTAX  CounterBasedGauge64 
		MAX-ACCESS read-only 
		STATUS current
		DESCRIPTION  "DoH Retry with TCP SG" 
		::={ acosSlbHttpProxyS 314 } 

		dohGetUriTooLong OBJECT-TYPE
		SYNTAX  CounterBasedGauge64 
		MAX-ACCESS read-only 
		STATUS current
		DESCRIPTION  "DoH GET URI too long" 
		::={ acosSlbHttpProxyS 315 } 

		dohPostPayloadTooLarge OBJECT-TYPE
		SYNTAX  CounterBasedGauge64 
		MAX-ACCESS read-only 
		STATUS current
		DESCRIPTION  "DoH POST Payload too large" 
		::={ acosSlbHttpProxyS 316 } 

		dohDnsMalformedQuery OBJECT-TYPE
		SYNTAX  CounterBasedGauge64 
		MAX-ACCESS read-only 
		STATUS current
		DESCRIPTION  "DoH DNS Malformed Query" 
		::={ acosSlbHttpProxyS 317 } 

		dohDnsRespRcodeErrFormat OBJECT-TYPE
		SYNTAX  CounterBasedGauge64 
		MAX-ACCESS read-only 
		STATUS current
		DESCRIPTION  "DoH DNS Response rcode ERR_FORMAT" 
		::={ acosSlbHttpProxyS 318 } 

		dohDnsRespRcodeErrServer OBJECT-TYPE
		SYNTAX  CounterBasedGauge64 
		MAX-ACCESS read-only 
		STATUS current
		DESCRIPTION  "DoH DNS Response rcode ERR_SERVER" 
		::={ acosSlbHttpProxyS 319 } 

		dohDnsRespRcodeErrName OBJECT-TYPE
		SYNTAX  CounterBasedGauge64 
		MAX-ACCESS read-only 
		STATUS current
		DESCRIPTION  "DoH DNS Response rcode ERR_NAME" 
		::={ acosSlbHttpProxyS 320 } 

		dohDnsRespRcodeErrType OBJECT-TYPE
		SYNTAX  CounterBasedGauge64 
		MAX-ACCESS read-only 
		STATUS current
		DESCRIPTION  "DoH DNS Response rcode ERR_TYPE" 
		::={ acosSlbHttpProxyS 321 } 

		dohDnsRespRcodeRefuse OBJECT-TYPE
		SYNTAX  CounterBasedGauge64 
		MAX-ACCESS read-only 
		STATUS current
		DESCRIPTION  "DoH DNS Response rcode REFUSE" 
		::={ acosSlbHttpProxyS 322 } 

		dohDnsRespRcodeYxdomain OBJECT-TYPE
		SYNTAX  CounterBasedGauge64 
		MAX-ACCESS read-only 
		STATUS current
		DESCRIPTION  "DoH DNS Response rcode YXDOMAIN" 
		::={ acosSlbHttpProxyS 323 } 

		dohDnsRespRcodeYxrrset OBJECT-TYPE
		SYNTAX  CounterBasedGauge64 
		MAX-ACCESS read-only 
		STATUS current
		DESCRIPTION  "DoH DNS Response rcode YXRRSET" 
		::={ acosSlbHttpProxyS 324 } 

		dohDnsRespRcodeNxrrset OBJECT-TYPE
		SYNTAX  CounterBasedGauge64 
		MAX-ACCESS read-only 
		STATUS current
		DESCRIPTION  "DoH DNS Response rcode NXRRSET" 
		::={ acosSlbHttpProxyS 325 } 

		dohDnsRespRcodeNotauth OBJECT-TYPE
		SYNTAX  CounterBasedGauge64 
		MAX-ACCESS read-only 
		STATUS current
		DESCRIPTION  "DoH DNS Response rcode NOTAUTH" 
		::={ acosSlbHttpProxyS 326 } 

		dohDnsRespRcodeNotzone OBJECT-TYPE
		SYNTAX  CounterBasedGauge64 
		MAX-ACCESS read-only 
		STATUS current
		DESCRIPTION  "DoH DNS Response rcode NOTZONE" 
		::={ acosSlbHttpProxyS 327 } 

		dohDnsRespRcodeOther OBJECT-TYPE
		SYNTAX  CounterBasedGauge64 
		MAX-ACCESS read-only 
		STATUS current
		DESCRIPTION  "DoH DNS Response rcode OTHER" 
		::={ acosSlbHttpProxyS 328 } 

		compressionBeforeBr OBJECT-TYPE
		SYNTAX  CounterBasedGauge64 
		MAX-ACCESS read-only 
		STATUS current
		DESCRIPTION  "Tot data before brotli compress" 
		::={ acosSlbHttpProxyS 329 } 

		compressionAfterBr OBJECT-TYPE
		SYNTAX  CounterBasedGauge64 
		MAX-ACCESS read-only 
		STATUS current
		DESCRIPTION  "Tot data after brotli compress" 
		::={ acosSlbHttpProxyS 330 } 

		compressionBeforeTotal OBJECT-TYPE
		SYNTAX  CounterBasedGauge64 
		MAX-ACCESS read-only 
		STATUS current
		DESCRIPTION  "Tot data before compress" 
		::={ acosSlbHttpProxyS 331 } 

		compressionAfterTotal OBJECT-TYPE
		SYNTAX  CounterBasedGauge64 
		MAX-ACCESS read-only 
		STATUS current
		DESCRIPTION  "Tot data after compress" 
		::={ acosSlbHttpProxyS 332 } 

		decompressionBeforeBr OBJECT-TYPE
		SYNTAX  CounterBasedGauge64 
		MAX-ACCESS read-only 
		STATUS current
		DESCRIPTION  "Tot data before brotli decompress" 
		::={ acosSlbHttpProxyS 333 } 

		decompressionAfterBr OBJECT-TYPE
		SYNTAX  CounterBasedGauge64 
		MAX-ACCESS read-only 
		STATUS current
		DESCRIPTION  "Tot data after brotli decompress" 
		::={ acosSlbHttpProxyS 334 } 

		decompressionBeforeTotal OBJECT-TYPE
		SYNTAX  CounterBasedGauge64 
		MAX-ACCESS read-only 
		STATUS current
		DESCRIPTION  "Tot data before decompress" 
		::={ acosSlbHttpProxyS 335 } 

		decompressionAfterTotal OBJECT-TYPE
		SYNTAX  CounterBasedGauge64 
		MAX-ACCESS read-only 
		STATUS current
		DESCRIPTION  "Tot data after decompress" 
		::={ acosSlbHttpProxyS 336 } 

		compressRspBr OBJECT-TYPE
		SYNTAX  CounterBasedGauge64 
		MAX-ACCESS read-only 
		STATUS current
		DESCRIPTION  "Compress req with brotli" 
		::={ acosSlbHttpProxyS 338 } 

		compressRspTotal OBJECT-TYPE
		SYNTAX  CounterBasedGauge64 
		MAX-ACCESS read-only 
		STATUS current
		DESCRIPTION  "Compress req" 
		::={ acosSlbHttpProxyS 339 } 

		h2upContentLengthAlias OBJECT-TYPE
		SYNTAX  CounterBasedGauge64 
		MAX-ACCESS read-only 
		STATUS current
		DESCRIPTION  "HTTP2 content length alias" 
		::={ acosSlbHttpProxyS 340 } 

		malformedH2upHeaderValue OBJECT-TYPE
		SYNTAX  CounterBasedGauge64 
		MAX-ACCESS read-only 
		STATUS current
		DESCRIPTION  "Malformed HTTP2 header value" 
		::={ acosSlbHttpProxyS 341 } 

		malformedH2upSchemeValue OBJECT-TYPE
		SYNTAX  CounterBasedGauge64 
		MAX-ACCESS read-only 
		STATUS current
		DESCRIPTION  "Malformed HTTP2 scheme value" 
		::={ acosSlbHttpProxyS 342 } 

		h2upWithTransferEncoding OBJECT-TYPE
		SYNTAX  CounterBasedGauge64 
		MAX-ACCESS read-only 
		STATUS current
		DESCRIPTION  "HTTP2 with transfer-encoding header" 
		::={ acosSlbHttpProxyS 343 } 

		multipleContentLength OBJECT-TYPE
		SYNTAX  CounterBasedGauge64 
		MAX-ACCESS read-only 
		STATUS current
		DESCRIPTION  "Multiple content-length headers" 
		::={ acosSlbHttpProxyS 344 } 

		multipleTransferEncoding OBJECT-TYPE
		SYNTAX  CounterBasedGauge64 
		MAX-ACCESS read-only 
		STATUS current
		DESCRIPTION  "Multiple transfer-encoding headers" 
		::={ acosSlbHttpProxyS 345 } 

		transferEncodingAndContentLength OBJECT-TYPE
		SYNTAX  CounterBasedGauge64 
		MAX-ACCESS read-only 
		STATUS current
		DESCRIPTION  "Transfer-encoding header with Content-Length header" 
		::={ acosSlbHttpProxyS 346 } 

		getAndPayload OBJECT-TYPE
		SYNTAX  CounterBasedGauge64 
		MAX-ACCESS read-only 
		STATUS current
		DESCRIPTION  "GET method with content-length header or transfer-encoding header" 
		::={ acosSlbHttpProxyS 347 } 

		h2upWithHostAndAuth OBJECT-TYPE
		SYNTAX  CounterBasedGauge64 
		MAX-ACCESS read-only 
		STATUS current
		DESCRIPTION  "HTTP2 with host header and authority header" 
		::={ acosSlbHttpProxyS 348 } 

		reqHttp3 OBJECT-TYPE
		SYNTAX  CounterBasedGauge64 
		MAX-ACCESS read-only 
		STATUS current
		DESCRIPTION  "Request 3.0" 
		::={ acosSlbHttpProxyS 349 } 

		responseHttp3 OBJECT-TYPE
		SYNTAX  CounterBasedGauge64 
		MAX-ACCESS read-only 
		STATUS current
		DESCRIPTION  "Resp 3.0" 
		::={ acosSlbHttpProxyS 350 } 

		headerFilterRuleHit OBJECT-TYPE
		SYNTAX  CounterBasedGauge64 
		MAX-ACCESS read-only 
		STATUS current
		DESCRIPTION  "Hit header filter rule" 
		::={ acosSlbHttpProxyS 351 } 

		http1ClientIdleTimeout OBJECT-TYPE
		SYNTAX  CounterBasedGauge64 
		MAX-ACCESS read-only 
		STATUS current
		DESCRIPTION  "HTTP1 client idle timeout" 
		::={ acosSlbHttpProxyS 352 } 

		http2ClientIdleTimeout OBJECT-TYPE
		SYNTAX  CounterBasedGauge64 
		MAX-ACCESS read-only 
		STATUS current
		DESCRIPTION  "HTTP2 client idle timeout" 
		::={ acosSlbHttpProxyS 353 } 

		httpDisallowedMethods OBJECT-TYPE
		SYNTAX  CounterBasedGauge64 
		MAX-ACCESS read-only 
		STATUS current
		DESCRIPTION  "HTTP disallowed methods" 
		::={ acosSlbHttpProxyS 354 } 

		httpAllowedMethods OBJECT-TYPE
		SYNTAX  CounterBasedGauge64 
		MAX-ACCESS read-only 
		STATUS current
		DESCRIPTION  "HTTP allowed methods" 
		::={ acosSlbHttpProxyS 355 } 

		upgradeToNewProxy OBJECT-TYPE
		SYNTAX  CounterBasedGauge64 
		MAX-ACCESS read-only 
		STATUS current
		DESCRIPTION  "H2C upgrade" 
		::={ acosSlbHttpProxyS 356 } 

		delH2cHeader OBJECT-TYPE
		SYNTAX  CounterBasedGauge64 
		MAX-ACCESS read-only 
		STATUS current
		DESCRIPTION  "H2C header deletion" 
		::={ acosSlbHttpProxyS 357 } 

		reqHttp11NewProxy OBJECT-TYPE
		SYNTAX  CounterBasedGauge64 
		MAX-ACCESS read-only 
		STATUS current
		DESCRIPTION  "Request 1.1 (new proxy)" 
		::={ acosSlbHttpProxyS 358 } 

		transactionLimited OBJECT-TYPE
		SYNTAX  CounterBasedGauge64 
		MAX-ACCESS read-only 
		STATUS current
		DESCRIPTION  "Transaction limited" 
		::={ acosSlbHttpProxyS 359 } 

acosSlbRateLimitLog                 OBJECT IDENTIFIER ::= { acosSlb 47 }
acosSlbRateLimitLogS                OBJECT IDENTIFIER ::= { acosSlbRateLimitLog 1 }

		totalLogTimes OBJECT-TYPE
		SYNTAX  CounterBasedGauge64 
		MAX-ACCESS read-only 
		STATUS current
		DESCRIPTION  "Total log times" 
		::={ acosSlbRateLimitLogS 1 } 

		totalLogMsg OBJECT-TYPE
		SYNTAX  CounterBasedGauge64 
		MAX-ACCESS read-only 
		STATUS current
		DESCRIPTION  "Total log messages" 
		::={ acosSlbRateLimitLogS 2 } 

		localLogMsg OBJECT-TYPE
		SYNTAX  CounterBasedGauge64 
		MAX-ACCESS read-only 
		STATUS current
		DESCRIPTION  "Local log messages" 
		::={ acosSlbRateLimitLogS 3 } 

		remoteLogMsg OBJECT-TYPE
		SYNTAX  CounterBasedGauge64 
		MAX-ACCESS read-only 
		STATUS current
		DESCRIPTION  "Remote log messages" 
		::={ acosSlbRateLimitLogS 4 } 

		localLogRate OBJECT-TYPE
		SYNTAX  CounterBasedGauge64 
		MAX-ACCESS read-only 
		STATUS current
		DESCRIPTION  "Local rate (per sec)" 
		::={ acosSlbRateLimitLogS 5 } 

		remoteLogRate OBJECT-TYPE
		SYNTAX  CounterBasedGauge64 
		MAX-ACCESS read-only 
		STATUS current
		DESCRIPTION  "Remote rate (per sec)" 
		::={ acosSlbRateLimitLogS 6 } 

		msgTooBig OBJECT-TYPE
		SYNTAX  CounterBasedGauge64 
		MAX-ACCESS read-only 
		STATUS current
		DESCRIPTION  "Log message too big" 
		::={ acosSlbRateLimitLogS 7 } 

		buffAllocFail OBJECT-TYPE
		SYNTAX  CounterBasedGauge64 
		MAX-ACCESS read-only 
		STATUS current
		DESCRIPTION  "Buffer alloc fail" 
		::={ acosSlbRateLimitLogS 8 } 

		slbRateLimitLogNoRoute OBJECT-TYPE
		SYNTAX  CounterBasedGauge64 
		MAX-ACCESS read-only 
		STATUS current
		DESCRIPTION  "No route" 
		::={ acosSlbRateLimitLogS 9 } 

		buffSendFail OBJECT-TYPE
		SYNTAX  CounterBasedGauge64 
		MAX-ACCESS read-only 
		STATUS current
		DESCRIPTION  "Buffer send fail" 
		::={ acosSlbRateLimitLogS 10 } 

		allocConn OBJECT-TYPE
		SYNTAX  CounterBasedGauge64 
		MAX-ACCESS read-only 
		STATUS current
		DESCRIPTION  "Log-session alloc" 
		::={ acosSlbRateLimitLogS 11 } 

		freeConn OBJECT-TYPE
		SYNTAX  CounterBasedGauge64 
		MAX-ACCESS read-only 
		STATUS current
		DESCRIPTION  "Log-session free" 
		::={ acosSlbRateLimitLogS 12 } 

		connAllocFail OBJECT-TYPE
		SYNTAX  CounterBasedGauge64 
		MAX-ACCESS read-only 
		STATUS current
		DESCRIPTION  "Log-session alloc fail" 
		::={ acosSlbRateLimitLogS 13 } 

		noRepeatMsg OBJECT-TYPE
		SYNTAX  CounterBasedGauge64 
		MAX-ACCESS read-only 
		STATUS current
		DESCRIPTION  "No repeat message" 
		::={ acosSlbRateLimitLogS 14 } 

		localLogDropped OBJECT-TYPE
		SYNTAX  CounterBasedGauge64 
		MAX-ACCESS read-only 
		STATUS current
		DESCRIPTION  "Local log dropped due to rate-limit" 
		::={ acosSlbRateLimitLogS 15 } 

acosSlbL4                           OBJECT IDENTIFIER ::= { acosSlb 48 }
acosSlbL4S                          OBJECT IDENTIFIER ::= { acosSlbL4 1 }

		intcp OBJECT-TYPE
		SYNTAX  CounterBasedGauge64 
		MAX-ACCESS read-only 
		STATUS current
		DESCRIPTION  "TCP received" 
		::={ acosSlbL4S 1 } 

		synreceived OBJECT-TYPE
		SYNTAX  CounterBasedGauge64 
		MAX-ACCESS read-only 
		STATUS current
		DESCRIPTION  "TCP SYN received" 
		::={ acosSlbL4S 2 } 

		tcpFwdLastAck OBJECT-TYPE
		SYNTAX  CounterBasedGauge64 
		MAX-ACCESS read-only 
		STATUS current
		DESCRIPTION  "L4 rcv fwd last ACK" 
		::={ acosSlbL4S 3 } 

		tcpRevLastAck OBJECT-TYPE
		SYNTAX  CounterBasedGauge64 
		MAX-ACCESS read-only 
		STATUS current
		DESCRIPTION  "L4 rcv rev last ACK" 
		::={ acosSlbL4S 4 } 

		tcpRevFin OBJECT-TYPE
		SYNTAX  CounterBasedGauge64 
		MAX-ACCESS read-only 
		STATUS current
		DESCRIPTION  "L4 rcv rev FIN" 
		::={ acosSlbL4S 5 } 

		tcpFwdFin OBJECT-TYPE
		SYNTAX  CounterBasedGauge64 
		MAX-ACCESS read-only 
		STATUS current
		DESCRIPTION  "L4 rcv fwd FIN" 
		::={ acosSlbL4S 6 } 

		tcpFwdAckfin OBJECT-TYPE
		SYNTAX  CounterBasedGauge64 
		MAX-ACCESS read-only 
		STATUS current
		DESCRIPTION  "L4 rcv fwd FIN|ACK" 
		::={ acosSlbL4S 7 } 

		inudp OBJECT-TYPE
		SYNTAX  CounterBasedGauge64 
		MAX-ACCESS read-only 
		STATUS current
		DESCRIPTION  "UDP received" 
		::={ acosSlbL4S 8 } 

		syncookiessent OBJECT-TYPE
		SYNTAX  CounterBasedGauge64 
		MAX-ACCESS read-only 
		STATUS current
		DESCRIPTION  "TCP SYN cookie snt" 
		::={ acosSlbL4S 9 } 

		syncookiessentTs OBJECT-TYPE
		SYNTAX  CounterBasedGauge64 
		MAX-ACCESS read-only 
		STATUS current
		DESCRIPTION  "TCP SYN cookie snt ts" 
		::={ acosSlbL4S 10 } 

		syncookiessentfailed OBJECT-TYPE
		SYNTAX  CounterBasedGauge64 
		MAX-ACCESS read-only 
		STATUS current
		DESCRIPTION  "TCP SYN cookie snt fail" 
		::={ acosSlbL4S 11 } 

		outrst OBJECT-TYPE
		SYNTAX  CounterBasedGauge64 
		MAX-ACCESS read-only 
		STATUS current
		DESCRIPTION  "TCP out RST" 
		::={ acosSlbL4S 12 } 

		outrstNosyn OBJECT-TYPE
		SYNTAX  CounterBasedGauge64 
		MAX-ACCESS read-only 
		STATUS current
		DESCRIPTION  "TCP out RST no SYN" 
		::={ acosSlbL4S 13 } 

		outrstBroker OBJECT-TYPE
		SYNTAX  CounterBasedGauge64 
		MAX-ACCESS read-only 
		STATUS current
		DESCRIPTION  "TCP out RST L4 proxy" 
		::={ acosSlbL4S 14 } 

		outrstAckAttack OBJECT-TYPE
		SYNTAX  CounterBasedGauge64 
		MAX-ACCESS read-only 
		STATUS current
		DESCRIPTION  "TCP out RST ACK attack" 
		::={ acosSlbL4S 15 } 

		outrstAflex OBJECT-TYPE
		SYNTAX  CounterBasedGauge64 
		MAX-ACCESS read-only 
		STATUS current
		DESCRIPTION  "TCP out RST aFleX" 
		::={ acosSlbL4S 16 } 

		outrstStaleSess OBJECT-TYPE
		SYNTAX  CounterBasedGauge64 
		MAX-ACCESS read-only 
		STATUS current
		DESCRIPTION  "TCP out RST stale sess" 
		::={ acosSlbL4S 17 } 

		synStaleSess OBJECT-TYPE
		SYNTAX  CounterBasedGauge64 
		MAX-ACCESS read-only 
		STATUS current
		DESCRIPTION  "SYN stale sess drop" 
		::={ acosSlbL4S 18 } 

		outrstTcpproxy OBJECT-TYPE
		SYNTAX  CounterBasedGauge64 
		MAX-ACCESS read-only 
		STATUS current
		DESCRIPTION  "TCP out RST TCP proxy" 
		::={ acosSlbL4S 19 } 

		svrselfail OBJECT-TYPE
		SYNTAX  CounterBasedGauge64 
		MAX-ACCESS read-only 
		STATUS current
		DESCRIPTION  "Server sel failure" 
		::={ acosSlbL4S 20 } 

		noroute OBJECT-TYPE
		SYNTAX  CounterBasedGauge64 
		MAX-ACCESS read-only 
		STATUS current
		DESCRIPTION  "IP out noroute" 
		::={ acosSlbL4S 21 } 

		snatFail OBJECT-TYPE
		SYNTAX  CounterBasedGauge64 
		MAX-ACCESS read-only 
		STATUS current
		DESCRIPTION  "Source NAT failure" 
		::={ acosSlbL4S 22 } 

		snatNoFwdRoute OBJECT-TYPE
		SYNTAX  CounterBasedGauge64 
		MAX-ACCESS read-only 
		STATUS current
		DESCRIPTION  "Source NAT no fwd route" 
		::={ acosSlbL4S 23 } 

		snatNoRevRoute OBJECT-TYPE
		SYNTAX  CounterBasedGauge64 
		MAX-ACCESS read-only 
		STATUS current
		DESCRIPTION  "Source NAT no rev route" 
		::={ acosSlbL4S 24 } 

		snatIcmpErrorProcess OBJECT-TYPE
		SYNTAX  CounterBasedGauge64 
		MAX-ACCESS read-only 
		STATUS current
		DESCRIPTION  "Source NAT ICMP Process" 
		::={ acosSlbL4S 25 } 

		snatIcmpNoMatch OBJECT-TYPE
		SYNTAX  CounterBasedGauge64 
		MAX-ACCESS read-only 
		STATUS current
		DESCRIPTION  "Source NAT ICMP No Match" 
		::={ acosSlbL4S 26 } 

		smartNatIdMismatch OBJECT-TYPE
		SYNTAX  CounterBasedGauge64 
		MAX-ACCESS read-only 
		STATUS current
		DESCRIPTION  "Auto NAT id mismatch" 
		::={ acosSlbL4S 27 } 

		syncookiescheckfailed OBJECT-TYPE
		SYNTAX  CounterBasedGauge64 
		MAX-ACCESS read-only 
		STATUS current
		DESCRIPTION  "TCP SYN cookie failed" 
		::={ acosSlbL4S 28 } 

		novportDrop OBJECT-TYPE
		SYNTAX  CounterBasedGauge64 
		MAX-ACCESS read-only 
		STATUS current
		DESCRIPTION  "NAT no session drops" 
		::={ acosSlbL4S 29 } 

		noVportDrop OBJECT-TYPE
		SYNTAX  CounterBasedGauge64 
		MAX-ACCESS read-only 
		STATUS current
		DESCRIPTION  "vport not matching drops" 
		::={ acosSlbL4S 30 } 

		nosynDrop OBJECT-TYPE
		SYNTAX  CounterBasedGauge64 
		MAX-ACCESS read-only 
		STATUS current
		DESCRIPTION  "No SYN pkt drops" 
		::={ acosSlbL4S 31 } 

		nosynDropFin OBJECT-TYPE
		SYNTAX  CounterBasedGauge64 
		MAX-ACCESS read-only 
		STATUS current
		DESCRIPTION  "No SYN pkt drops - FIN" 
		::={ acosSlbL4S 32 } 

		nosynDropRst OBJECT-TYPE
		SYNTAX  CounterBasedGauge64 
		MAX-ACCESS read-only 
		STATUS current
		DESCRIPTION  "No SYN pkt drops - RST" 
		::={ acosSlbL4S 33 } 

		nosynDropAck OBJECT-TYPE
		SYNTAX  CounterBasedGauge64 
		MAX-ACCESS read-only 
		STATUS current
		DESCRIPTION  "No SYN pkt drops - ACK" 
		::={ acosSlbL4S 34 } 

		connlimitDrop OBJECT-TYPE
		SYNTAX  CounterBasedGauge64 
		MAX-ACCESS read-only 
		STATUS current
		DESCRIPTION  "Conn Limit drops" 
		::={ acosSlbL4S 35 } 

		connlimitReset OBJECT-TYPE
		SYNTAX  CounterBasedGauge64 
		MAX-ACCESS read-only 
		STATUS current
		DESCRIPTION  "Conn Limit resets" 
		::={ acosSlbL4S 36 } 

		connRateLimitDrop OBJECT-TYPE
		SYNTAX  CounterBasedGauge64 
		MAX-ACCESS read-only 
		STATUS current
		DESCRIPTION  "Conn rate limit drops" 
		::={ acosSlbL4S 37 } 

		connRateLimitReset OBJECT-TYPE
		SYNTAX  CounterBasedGauge64 
		MAX-ACCESS read-only 
		STATUS current
		DESCRIPTION  "Conn rate limit resets" 
		::={ acosSlbL4S 38 } 

		proxyNosockDrop OBJECT-TYPE
		SYNTAX  CounterBasedGauge64 
		MAX-ACCESS read-only 
		STATUS current
		DESCRIPTION  "Proxy no sock drops" 
		::={ acosSlbL4S 39 } 

		dropAflex OBJECT-TYPE
		SYNTAX  CounterBasedGauge64 
		MAX-ACCESS read-only 
		STATUS current
		DESCRIPTION  "aFleX drops" 
		::={ acosSlbL4S 40 } 

		sessAgedOut OBJECT-TYPE
		SYNTAX  CounterBasedGauge64 
		MAX-ACCESS read-only 
		STATUS current
		DESCRIPTION  "Session aged out" 
		::={ acosSlbL4S 41 } 

		tcpSessAgedOut OBJECT-TYPE
		SYNTAX  CounterBasedGauge64 
		MAX-ACCESS read-only 
		STATUS current
		DESCRIPTION  "TCP Session aged out" 
		::={ acosSlbL4S 42 } 

		udpSessAgedOut OBJECT-TYPE
		SYNTAX  CounterBasedGauge64 
		MAX-ACCESS read-only 
		STATUS current
		DESCRIPTION  "UDP Session aged out" 
		::={ acosSlbL4S 43 } 

		otherSessAgedOut OBJECT-TYPE
		SYNTAX  CounterBasedGauge64 
		MAX-ACCESS read-only 
		STATUS current
		DESCRIPTION  "Other Session aged out" 
		::={ acosSlbL4S 44 } 

		tcpNoSlb OBJECT-TYPE
		SYNTAX  CounterBasedGauge64 
		MAX-ACCESS read-only 
		STATUS current
		DESCRIPTION  "TCP no SLB" 
		::={ acosSlbL4S 45 } 

		udpNoSlb OBJECT-TYPE
		SYNTAX  CounterBasedGauge64 
		MAX-ACCESS read-only 
		STATUS current
		DESCRIPTION  "UDP no SLB" 
		::={ acosSlbL4S 46 } 

		throttleSyn OBJECT-TYPE
		SYNTAX  CounterBasedGauge64 
		MAX-ACCESS read-only 
		STATUS current
		DESCRIPTION  "SYN Throttle" 
		::={ acosSlbL4S 47 } 

		dropGslb OBJECT-TYPE
		SYNTAX  CounterBasedGauge64 
		MAX-ACCESS read-only 
		STATUS current
		DESCRIPTION  "Drop GSLB" 
		::={ acosSlbL4S 48 } 

		inbandHmRetry OBJECT-TYPE
		SYNTAX  CounterBasedGauge64 
		MAX-ACCESS read-only 
		STATUS current
		DESCRIPTION  "Inband HM retry" 
		::={ acosSlbL4S 49 } 

		inbandHmReassign OBJECT-TYPE
		SYNTAX  CounterBasedGauge64 
		MAX-ACCESS read-only 
		STATUS current
		DESCRIPTION  "Inband HM reassign" 
		::={ acosSlbL4S 50 } 

		autoReassign OBJECT-TYPE
		SYNTAX  CounterBasedGauge64 
		MAX-ACCESS read-only 
		STATUS current
		DESCRIPTION  "Auto-reselect server" 
		::={ acosSlbL4S 51 } 

		fastAgingSet OBJECT-TYPE
		SYNTAX  CounterBasedGauge64 
		MAX-ACCESS read-only 
		STATUS current
		DESCRIPTION  "Fast aging set" 
		::={ acosSlbL4S 52 } 

		fastAgingReset OBJECT-TYPE
		SYNTAX  CounterBasedGauge64 
		MAX-ACCESS read-only 
		STATUS current
		DESCRIPTION  "Fast aging reset" 
		::={ acosSlbL4S 53 } 

		dnsPolicyDrop OBJECT-TYPE
		SYNTAX  CounterBasedGauge64 
		MAX-ACCESS read-only 
		STATUS current
		DESCRIPTION  "DNS Policy Drop" 
		::={ acosSlbL4S 54 } 

		tcpInvalidDrop OBJECT-TYPE
		SYNTAX  CounterBasedGauge64 
		MAX-ACCESS read-only 
		STATUS current
		DESCRIPTION  "TCP invalid drop" 
		::={ acosSlbL4S 55 } 

		anomalyOutSeq OBJECT-TYPE
		SYNTAX  CounterBasedGauge64 
		MAX-ACCESS read-only 
		STATUS current
		DESCRIPTION  "Anomaly out of sequence" 
		::={ acosSlbL4S 56 } 

		anomalyZeroWin OBJECT-TYPE
		SYNTAX  CounterBasedGauge64 
		MAX-ACCESS read-only 
		STATUS current
		DESCRIPTION  "Anomaly zero window" 
		::={ acosSlbL4S 57 } 

		anomalyBadContent OBJECT-TYPE
		SYNTAX  CounterBasedGauge64 
		MAX-ACCESS read-only 
		STATUS current
		DESCRIPTION  "Anomaly bad content" 
		::={ acosSlbL4S 58 } 

		anomalyPbslbDrop OBJECT-TYPE
		SYNTAX  CounterBasedGauge64 
		MAX-ACCESS read-only 
		STATUS current
		DESCRIPTION  "Anomaly pbslb drop" 
		::={ acosSlbL4S 59 } 

		noResourseDrop OBJECT-TYPE
		SYNTAX  CounterBasedGauge64 
		MAX-ACCESS read-only 
		STATUS current
		DESCRIPTION  "No resource drop" 
		::={ acosSlbL4S 60 } 

		resetUnknownConn OBJECT-TYPE
		SYNTAX  CounterBasedGauge64 
		MAX-ACCESS read-only 
		STATUS current
		DESCRIPTION  "Reset unknown conn" 
		::={ acosSlbL4S 61 } 

		resetL7OnFailover OBJECT-TYPE
		SYNTAX  CounterBasedGauge64 
		MAX-ACCESS read-only 
		STATUS current
		DESCRIPTION  "RST L7 on failover" 
		::={ acosSlbL4S 62 } 

		ignoreMsl OBJECT-TYPE
		SYNTAX  CounterBasedGauge64 
		MAX-ACCESS read-only 
		STATUS current
		DESCRIPTION  "ignore msl" 
		::={ acosSlbL4S 63 } 

		l2Dsr OBJECT-TYPE
		SYNTAX  CounterBasedGauge64 
		MAX-ACCESS read-only 
		STATUS current
		DESCRIPTION  "L2 DSR received" 
		::={ acosSlbL4S 64 } 

		l3Dsr OBJECT-TYPE
		SYNTAX  CounterBasedGauge64 
		MAX-ACCESS read-only 
		STATUS current
		DESCRIPTION  "L3 DSR received" 
		::={ acosSlbL4S 65 } 

		portPreserveAttempt OBJECT-TYPE
		SYNTAX  CounterBasedGauge64 
		MAX-ACCESS read-only 
		STATUS current
		DESCRIPTION  "NAT Port Preserve Try" 
		::={ acosSlbL4S 66 } 

		portPreserveSucc OBJECT-TYPE
		SYNTAX  CounterBasedGauge64 
		MAX-ACCESS read-only 
		STATUS current
		DESCRIPTION  "NAT Port Preserve Succ" 
		::={ acosSlbL4S 67 } 

		tcpsyndataDrop OBJECT-TYPE
		SYNTAX  CounterBasedGauge64 
		MAX-ACCESS read-only 
		STATUS current
		DESCRIPTION  "TCP SYN With Data Drop" 
		::={ acosSlbL4S 68 } 

		tcpotherflagsDrop OBJECT-TYPE
		SYNTAX  CounterBasedGauge64 
		MAX-ACCESS read-only 
		STATUS current
		DESCRIPTION  "TCP SYN Other Flags Drop" 
		::={ acosSlbL4S 69 } 

		bwRateLimitExceed OBJECT-TYPE
		SYNTAX  CounterBasedGauge64 
		MAX-ACCESS read-only 
		STATUS current
		DESCRIPTION  "BW-Limit Exceed drop" 
		::={ acosSlbL4S 70 } 

		bwWatermarkDrop OBJECT-TYPE
		SYNTAX  CounterBasedGauge64 
		MAX-ACCESS read-only 
		STATUS current
		DESCRIPTION  "BW-Watermark drop" 
		::={ acosSlbL4S 71 } 

		l4CpsExceed OBJECT-TYPE
		SYNTAX  CounterBasedGauge64 
		MAX-ACCESS read-only 
		STATUS current
		DESCRIPTION  "L4 CPS exceed drop" 
		::={ acosSlbL4S 72 } 

		natCpsExceed OBJECT-TYPE
		SYNTAX  CounterBasedGauge64 
		MAX-ACCESS read-only 
		STATUS current
		DESCRIPTION  "NAT CPS exceed drop" 
		::={ acosSlbL4S 73 } 

		l7CpsExceed OBJECT-TYPE
		SYNTAX  CounterBasedGauge64 
		MAX-ACCESS read-only 
		STATUS current
		DESCRIPTION  "L7 CPS exceed drop" 
		::={ acosSlbL4S 74 } 

		sslCpsExceed OBJECT-TYPE
		SYNTAX  CounterBasedGauge64 
		MAX-ACCESS read-only 
		STATUS current
		DESCRIPTION  "SSL CPS exceed drop" 
		::={ acosSlbL4S 75 } 

		sslTptExceed OBJECT-TYPE
		SYNTAX  CounterBasedGauge64 
		MAX-ACCESS read-only 
		STATUS current
		DESCRIPTION  "SSL TPT exceed drop" 
		::={ acosSlbL4S 76 } 

		sslWatermarkDrop OBJECT-TYPE
		SYNTAX  CounterBasedGauge64 
		MAX-ACCESS read-only 
		STATUS current
		DESCRIPTION  "SSL TPT-Watermark drop" 
		::={ acosSlbL4S 77 } 

		concurrentConnExceed OBJECT-TYPE
		SYNTAX  CounterBasedGauge64 
		MAX-ACCESS read-only 
		STATUS current
		DESCRIPTION  "L3V Conn Limit Drop" 
		::={ acosSlbL4S 78 } 

		svrSynHandshakeFail OBJECT-TYPE
		SYNTAX  CounterBasedGauge64 
		MAX-ACCESS read-only 
		STATUS current
		DESCRIPTION  "L4 server handshake fail" 
		::={ acosSlbL4S 79 } 

		statelessConnTimeout OBJECT-TYPE
		SYNTAX  CounterBasedGauge64 
		MAX-ACCESS read-only 
		STATUS current
		DESCRIPTION  "L4 stateless Conn TO" 
		::={ acosSlbL4S 80 } 

		tcpAxRexmitSyn OBJECT-TYPE
		SYNTAX  CounterBasedGauge64 
		MAX-ACCESS read-only 
		STATUS current
		DESCRIPTION  "L4 AX re-xmit SYN" 
		::={ acosSlbL4S 81 } 

		tcpSynRcvAck OBJECT-TYPE
		SYNTAX  CounterBasedGauge64 
		MAX-ACCESS read-only 
		STATUS current
		DESCRIPTION  "L4 rcv ACK on SYN" 
		::={ acosSlbL4S 82 } 

		tcpSynRcvRst OBJECT-TYPE
		SYNTAX  CounterBasedGauge64 
		MAX-ACCESS read-only 
		STATUS current
		DESCRIPTION  "L4 rcv RST on SYN" 
		::={ acosSlbL4S 83 } 

		tcpSessNoestAgedOut OBJECT-TYPE
		SYNTAX  CounterBasedGauge64 
		MAX-ACCESS read-only 
		STATUS current
		DESCRIPTION  "TCP no-Est Sess aged out" 
		::={ acosSlbL4S 84 } 

		tcpSessNoestCsynRcvAgedOut OBJECT-TYPE
		SYNTAX  CounterBasedGauge64 
		MAX-ACCESS read-only 
		STATUS current
		DESCRIPTION  "no-Est CSYN rcv aged out" 
		::={ acosSlbL4S 85 } 

		tcpSessNoestSsynXmitAgedOut OBJECT-TYPE
		SYNTAX  CounterBasedGauge64 
		MAX-ACCESS read-only 
		STATUS current
		DESCRIPTION  "no-Est SSYN snt aged out" 
		::={ acosSlbL4S 86 } 

		tcpRexmitSyn OBJECT-TYPE
		SYNTAX  CounterBasedGauge64 
		MAX-ACCESS read-only 
		STATUS current
		DESCRIPTION  "L4 rcv rexmit SYN" 
		::={ acosSlbL4S 87 } 

		tcpRexmitSynDelq OBJECT-TYPE
		SYNTAX  CounterBasedGauge64 
		MAX-ACCESS read-only 
		STATUS current
		DESCRIPTION  "L4 rcv rexmit SYN (delq)" 
		::={ acosSlbL4S 88 } 

		tcpRexmitSynack OBJECT-TYPE
		SYNTAX  CounterBasedGauge64 
		MAX-ACCESS read-only 
		STATUS current
		DESCRIPTION  "L4 rcv rexmit SYN|ACK" 
		::={ acosSlbL4S 89 } 

		tcpRexmitSynackDelq OBJECT-TYPE
		SYNTAX  CounterBasedGauge64 
		MAX-ACCESS read-only 
		STATUS current
		DESCRIPTION  "L4 rcv rexmit SYN|ACK DQ" 
		::={ acosSlbL4S 90 } 

		tcpFwdFinDup OBJECT-TYPE
		SYNTAX  CounterBasedGauge64 
		MAX-ACCESS read-only 
		STATUS current
		DESCRIPTION  "L4 rcv fwd FIN dup" 
		::={ acosSlbL4S 91 } 

		tcpRevFinDup OBJECT-TYPE
		SYNTAX  CounterBasedGauge64 
		MAX-ACCESS read-only 
		STATUS current
		DESCRIPTION  "L4 rcv rev FIN dup" 
		::={ acosSlbL4S 92 } 

		tcpRevAckfin OBJECT-TYPE
		SYNTAX  CounterBasedGauge64 
		MAX-ACCESS read-only 
		STATUS current
		DESCRIPTION  "L4 rcv rev FIN|ACK" 
		::={ acosSlbL4S 93 } 

		tcpFwdRst OBJECT-TYPE
		SYNTAX  CounterBasedGauge64 
		MAX-ACCESS read-only 
		STATUS current
		DESCRIPTION  "L4 rcv fwd RST" 
		::={ acosSlbL4S 94 } 

		tcpRevRst OBJECT-TYPE
		SYNTAX  CounterBasedGauge64 
		MAX-ACCESS read-only 
		STATUS current
		DESCRIPTION  "L4 rcv rev RST" 
		::={ acosSlbL4S 95 } 

		udpReqOneplusNoResp OBJECT-TYPE
		SYNTAX  CounterBasedGauge64 
		MAX-ACCESS read-only 
		STATUS current
		DESCRIPTION  "L4 UDP reqs no rsp" 
		::={ acosSlbL4S 96 } 

		udpReqOneOneplusResp OBJECT-TYPE
		SYNTAX  CounterBasedGauge64 
		MAX-ACCESS read-only 
		STATUS current
		DESCRIPTION  "L4 UDP req rsps" 
		::={ acosSlbL4S 97 } 

		udpReqRespNotmatch OBJECT-TYPE
		SYNTAX  CounterBasedGauge64 
		MAX-ACCESS read-only 
		STATUS current
		DESCRIPTION  "L4 UDP req/rsp not match" 
		::={ acosSlbL4S 98 } 

		udpReqMoreResp OBJECT-TYPE
		SYNTAX  CounterBasedGauge64 
		MAX-ACCESS read-only 
		STATUS current
		DESCRIPTION  "L4 UDP req greater than rsps" 
		::={ acosSlbL4S 99 } 

		udpRespMoreReq OBJECT-TYPE
		SYNTAX  CounterBasedGauge64 
		MAX-ACCESS read-only 
		STATUS current
		DESCRIPTION  "L4 UDP rsps greater than reqs" 
		::={ acosSlbL4S 100 } 

		udpReqOneplus OBJECT-TYPE
		SYNTAX  CounterBasedGauge64 
		MAX-ACCESS read-only 
		STATUS current
		DESCRIPTION  "L4 UDP reqs" 
		::={ acosSlbL4S 101 } 

		udpRespOneplus OBJECT-TYPE
		SYNTAX  CounterBasedGauge64 
		MAX-ACCESS read-only 
		STATUS current
		DESCRIPTION  "L4 UDP rsps" 
		::={ acosSlbL4S 102 } 

		outSeqAckDrop OBJECT-TYPE
		SYNTAX  CounterBasedGauge64 
		MAX-ACCESS read-only 
		STATUS current
		DESCRIPTION  "Out of sequence ACK drop" 
		::={ acosSlbL4S 103 } 

		tcpEst OBJECT-TYPE
		SYNTAX  CounterBasedGauge64 
		MAX-ACCESS read-only 
		STATUS current
		DESCRIPTION  "L4 TCP Established" 
		::={ acosSlbL4S 104 } 

		synattack OBJECT-TYPE
		SYNTAX  CounterBasedGauge64 
		MAX-ACCESS read-only 
		STATUS current
		DESCRIPTION  "L4 SYN attack" 
		::={ acosSlbL4S 105 } 

		synRate OBJECT-TYPE
		SYNTAX  CounterBasedGauge64 
		MAX-ACCESS read-only 
		STATUS current
		DESCRIPTION  "TCP SYN rate per sec" 
		::={ acosSlbL4S 106 } 

		syncookieBuffDrop OBJECT-TYPE
		SYNTAX  CounterBasedGauge64 
		MAX-ACCESS read-only 
		STATUS current
		DESCRIPTION  "TCP SYN cookie buff drop" 
		::={ acosSlbL4S 107 } 

		syncookieBuffQueue OBJECT-TYPE
		SYNTAX  CounterBasedGauge64 
		MAX-ACCESS read-only 
		STATUS current
		DESCRIPTION  "TCP SYN cookie buff queue" 
		::={ acosSlbL4S 108 } 

		skipInsertClientIp OBJECT-TYPE
		SYNTAX  CounterBasedGauge64 
		MAX-ACCESS read-only 
		STATUS current
		DESCRIPTION  "Skip Insert-client-ip" 
		::={ acosSlbL4S 109 } 

		synreceivedHw OBJECT-TYPE
		SYNTAX  CounterBasedGauge64 
		MAX-ACCESS read-only 
		STATUS current
		DESCRIPTION  "TCP SYN (HW SYN cookie)" 
		::={ acosSlbL4S 110 } 

		dnsIdSwitch OBJECT-TYPE
		SYNTAX  CounterBasedGauge64 
		MAX-ACCESS read-only 
		STATUS current
		DESCRIPTION  "DNS query id switch" 
		::={ acosSlbL4S 111 } 

		serverDownDel OBJECT-TYPE
		SYNTAX  CounterBasedGauge64 
		MAX-ACCESS read-only 
		STATUS current
		DESCRIPTION  "Server Down Del switch" 
		::={ acosSlbL4S 112 } 

		dnssecSwitch OBJECT-TYPE
		SYNTAX  CounterBasedGauge64 
		MAX-ACCESS read-only 
		STATUS current
		DESCRIPTION  "DNSSEC SG switch" 
		::={ acosSlbL4S 113 } 

		rateDropResetUnkn OBJECT-TYPE
		SYNTAX  CounterBasedGauge64 
		MAX-ACCESS read-only 
		STATUS current
		DESCRIPTION  "Rate Drop reset" 
		::={ acosSlbL4S 114 } 

		tcpConnectionsClosed OBJECT-TYPE
		SYNTAX  CounterBasedGauge64 
		MAX-ACCESS read-only 
		STATUS current
		DESCRIPTION  "TCP Connections Closed" 
		::={ acosSlbL4S 115 } 

		gtpCInvalidPort OBJECT-TYPE
		SYNTAX  CounterBasedGauge64 
		MAX-ACCESS read-only 
		STATUS current
		DESCRIPTION  "Invalid Packet Received on GTP VIP" 
		::={ acosSlbL4S 116 } 

		gtpCInvalidHeader OBJECT-TYPE
		SYNTAX  CounterBasedGauge64 
		MAX-ACCESS read-only 
		STATUS current
		DESCRIPTION  "Invalid Header Received on GTP VIP" 
		::={ acosSlbL4S 117 } 

		gtpCInvalidMessage OBJECT-TYPE
		SYNTAX  CounterBasedGauge64 
		MAX-ACCESS read-only 
		STATUS current
		DESCRIPTION  "Non Create Session/PDP Context Request/Response Received on GTP VIP" 
		::={ acosSlbL4S 118 } 

		reselectSvrselfail OBJECT-TYPE
		SYNTAX  CounterBasedGauge64 
		MAX-ACCESS read-only 
		STATUS current
		DESCRIPTION  "Server reselect failure" 
		::={ acosSlbL4S 119 } 

		snatPortOverloadFail OBJECT-TYPE
		SYNTAX  CounterBasedGauge64 
		MAX-ACCESS read-only 
		STATUS current
		DESCRIPTION  "Snat port overload fail" 
		::={ acosSlbL4S 120 } 

		snatForcePreserveAlloc OBJECT-TYPE
		SYNTAX  CounterBasedGauge64 
		MAX-ACCESS read-only 
		STATUS current
		DESCRIPTION  "Snat port preserve allocated" 
		::={ acosSlbL4S 121 } 

		snatForcePreserveFree OBJECT-TYPE
		SYNTAX  CounterBasedGauge64 
		MAX-ACCESS read-only 
		STATUS current
		DESCRIPTION  "Snat port preserve freed" 
		::={ acosSlbL4S 122 } 

		proxyHeaderInsert OBJECT-TYPE
		SYNTAX  CounterBasedGauge64 
		MAX-ACCESS read-only 
		STATUS current
		DESCRIPTION  "PROXY protocol header inserted" 
		::={ acosSlbL4S 123 } 

		proxyHeaderRexmit OBJECT-TYPE
		SYNTAX  CounterBasedGauge64 
		MAX-ACCESS read-only 
		STATUS current
		DESCRIPTION  "PROXY protocol header retransmitted" 
		::={ acosSlbL4S 124 } 

		proxyProtError OBJECT-TYPE
		SYNTAX  CounterBasedGauge64 
		MAX-ACCESS read-only 
		STATUS current
		DESCRIPTION  "PROXY protocol error" 
		::={ acosSlbL4S 125 } 

		proxyProtDrop OBJECT-TYPE
		SYNTAX  CounterBasedGauge64 
		MAX-ACCESS read-only 
		STATUS current
		DESCRIPTION  "PROXY protocol drop" 
		::={ acosSlbL4S 126 } 

		slbGtpProxyPktRcvRr OBJECT-TYPE
		SYNTAX  CounterBasedGauge64 
		MAX-ACCESS read-only 
		STATUS current
		DESCRIPTION  "SLB GTP proxy packet received on RR" 
		::={ acosSlbL4S 127 } 

		slbGtpProxySmpMatch OBJECT-TYPE
		SYNTAX  CounterBasedGauge64 
		MAX-ACCESS read-only 
		STATUS current
		DESCRIPTION  "SLB GTP proxy helper session found" 
		::={ acosSlbL4S 128 } 

		slbGtpProxySmpNoMatch OBJECT-TYPE
		SYNTAX  CounterBasedGauge64 
		MAX-ACCESS read-only 
		STATUS current
		DESCRIPTION  "SLB GTP proxy helper session not found" 
		::={ acosSlbL4S 129 } 

		slbGtpProxyCProcessLocalRr OBJECT-TYPE
		SYNTAX  CounterBasedGauge64 
		MAX-ACCESS read-only 
		STATUS current
		DESCRIPTION  "SLB GTP proxy messageprocessed locally on RR" 
		::={ acosSlbL4S 130 } 

		slbGtpProxySmpCreationFailed OBJECT-TYPE
		SYNTAX  CounterBasedGauge64 
		MAX-ACCESS read-only 
		STATUS current
		DESCRIPTION  "SLB GTP proxy helper session creation failed" 
		::={ acosSlbL4S 131 } 

		slbGtpProxySmpCreated OBJECT-TYPE
		SYNTAX  CounterBasedGauge64 
		MAX-ACCESS read-only 
		STATUS current
		DESCRIPTION  "SLB GTP proxy helper session created" 
		::={ acosSlbL4S 132 } 

		slbGtpProxySmpFreeNotFound OBJECT-TYPE
		SYNTAX  CounterBasedGauge64 
		MAX-ACCESS read-only 
		STATUS current
		DESCRIPTION  "SLB GTP proxy session helper not found during cleanup" 
		::={ acosSlbL4S 133 } 

		slbGtpProxySmpFreed OBJECT-TYPE
		SYNTAX  CounterBasedGauge64 
		MAX-ACCESS read-only 
		STATUS current
		DESCRIPTION  "SLB GTP proxy session helper freed" 
		::={ acosSlbL4S 134 } 

		slbGtpProxyRetxRequests OBJECT-TYPE
		SYNTAX  CounterBasedGauge64 
		MAX-ACCESS read-only 
		STATUS current
		DESCRIPTION  "SLB GTP proxy retx requests" 
		::={ acosSlbL4S 135 } 

		pbslbEntryLimitExceed OBJECT-TYPE
		SYNTAX  CounterBasedGauge64 
		MAX-ACCESS read-only 
		STATUS current
		DESCRIPTION  "pbslb entry limit Exceed" 
		::={ acosSlbL4S 136 } 

		fastPathReroute OBJECT-TYPE
		SYNTAX  CounterBasedGauge64 
		MAX-ACCESS read-only 
		STATUS current
		DESCRIPTION  "Fast Path Reroute" 
		::={ acosSlbL4S 137 } 

		fastPathL2Reroute OBJECT-TYPE
		SYNTAX  CounterBasedGauge64 
		MAX-ACCESS read-only 
		STATUS current
		DESCRIPTION  "Fast Path L2 Reroute" 
		::={ acosSlbL4S 138 } 

acosSlbFastHttpProxy                OBJECT IDENTIFIER ::= { acosSlb 49 }
acosSlbFastHttpProxyS               OBJECT IDENTIFIER ::= { acosSlbFastHttpProxy 1 }

		num OBJECT-TYPE
		SYNTAX  CounterBasedGauge64 
		MAX-ACCESS read-only 
		STATUS current
		DESCRIPTION  "Num" 
		::={ acosSlbFastHttpProxyS 1 } 

		slbFastHttpProxyCurrProxy OBJECT-TYPE
		SYNTAX  CounterBasedGauge64 
		MAX-ACCESS read-only 
		STATUS current
		DESCRIPTION  "Curr Proxy Conns" 
		::={ acosSlbFastHttpProxyS 2 } 

		slbFastHttpProxyTotalProxy OBJECT-TYPE
		SYNTAX  CounterBasedGauge64 
		MAX-ACCESS read-only 
		STATUS current
		DESCRIPTION  "Total Proxy Conns" 
		::={ acosSlbFastHttpProxyS 3 } 

		slbFastHttpProxyReq OBJECT-TYPE
		SYNTAX  CounterBasedGauge64 
		MAX-ACCESS read-only 
		STATUS current
		DESCRIPTION  "HTTP requests" 
		::={ acosSlbFastHttpProxyS 4 } 

		reqSucc OBJECT-TYPE
		SYNTAX  CounterBasedGauge64 
		MAX-ACCESS read-only 
		STATUS current
		DESCRIPTION  "HTTP requests(succ)" 
		::={ acosSlbFastHttpProxyS 5 } 

		noproxy OBJECT-TYPE
		SYNTAX  CounterBasedGauge64 
		MAX-ACCESS read-only 
		STATUS current
		DESCRIPTION  "No proxy error" 
		::={ acosSlbFastHttpProxyS 6 } 

		slbFastHttpProxyClientRst OBJECT-TYPE
		SYNTAX  CounterBasedGauge64 
		MAX-ACCESS read-only 
		STATUS current
		DESCRIPTION  "Client RST" 
		::={ acosSlbFastHttpProxyS 7 } 

		slbFastHttpProxyServerRst OBJECT-TYPE
		SYNTAX  CounterBasedGauge64 
		MAX-ACCESS read-only 
		STATUS current
		DESCRIPTION  "Server RST" 
		::={ acosSlbFastHttpProxyS 8 } 

		notuple OBJECT-TYPE
		SYNTAX  CounterBasedGauge64 
		MAX-ACCESS read-only 
		STATUS current
		DESCRIPTION  "No tuple error" 
		::={ acosSlbFastHttpProxyS 9 } 

		parsereqFail OBJECT-TYPE
		SYNTAX  CounterBasedGauge64 
		MAX-ACCESS read-only 
		STATUS current
		DESCRIPTION  "Parse req fail" 
		::={ acosSlbFastHttpProxyS 10 } 

		slbFastHttpProxySrvSelFail OBJECT-TYPE
		SYNTAX  CounterBasedGauge64 
		MAX-ACCESS read-only 
		STATUS current
		DESCRIPTION  "Server selection fail" 
		::={ acosSlbFastHttpProxyS 11 } 

		fwdreqFail OBJECT-TYPE
		SYNTAX  CounterBasedGauge64 
		MAX-ACCESS read-only 
		STATUS current
		DESCRIPTION  "Fwd req fail" 
		::={ acosSlbFastHttpProxyS 12 } 

		fwdreqFailBuff OBJECT-TYPE
		SYNTAX  CounterBasedGauge64 
		MAX-ACCESS read-only 
		STATUS current
		DESCRIPTION  "Fwd req fail - buff" 
		::={ acosSlbFastHttpProxyS 13 } 

		fwdreqFailRport OBJECT-TYPE
		SYNTAX  CounterBasedGauge64 
		MAX-ACCESS read-only 
		STATUS current
		DESCRIPTION  "Fwd req fail - rport" 
		::={ acosSlbFastHttpProxyS 14 } 

		fwdreqFailRoute OBJECT-TYPE
		SYNTAX  CounterBasedGauge64 
		MAX-ACCESS read-only 
		STATUS current
		DESCRIPTION  "Fwd req fail - route" 
		::={ acosSlbFastHttpProxyS 15 } 

		fwdreqFailPersist OBJECT-TYPE
		SYNTAX  CounterBasedGauge64 
		MAX-ACCESS read-only 
		STATUS current
		DESCRIPTION  "Fwd req fail - persist" 
		::={ acosSlbFastHttpProxyS 16 } 

		fwdreqFailServer OBJECT-TYPE
		SYNTAX  CounterBasedGauge64 
		MAX-ACCESS read-only 
		STATUS current
		DESCRIPTION  "Fwd req fail - server" 
		::={ acosSlbFastHttpProxyS 17 } 

		fwdreqFailTuple OBJECT-TYPE
		SYNTAX  CounterBasedGauge64 
		MAX-ACCESS read-only 
		STATUS current
		DESCRIPTION  "Fwd req fail - tuple" 
		::={ acosSlbFastHttpProxyS 18 } 

		fwdreqdataFail OBJECT-TYPE
		SYNTAX  CounterBasedGauge64 
		MAX-ACCESS read-only 
		STATUS current
		DESCRIPTION  "Fwd req data fail" 
		::={ acosSlbFastHttpProxyS 19 } 

		slbFastHttpProxyReqRetran OBJECT-TYPE
		SYNTAX  CounterBasedGauge64 
		MAX-ACCESS read-only 
		STATUS current
		DESCRIPTION  "Packets retrans" 
		::={ acosSlbFastHttpProxyS 20 } 

		slbFastHttpProxyReqOfo OBJECT-TYPE
		SYNTAX  CounterBasedGauge64 
		MAX-ACCESS read-only 
		STATUS current
		DESCRIPTION  "Packets ofo" 
		::={ acosSlbFastHttpProxyS 21 } 

		serverResel OBJECT-TYPE
		SYNTAX  CounterBasedGauge64 
		MAX-ACCESS read-only 
		STATUS current
		DESCRIPTION  "Server reselection" 
		::={ acosSlbFastHttpProxyS 22 } 

		svrPremClose OBJECT-TYPE
		SYNTAX  CounterBasedGauge64 
		MAX-ACCESS read-only 
		STATUS current
		DESCRIPTION  "Server premature close" 
		::={ acosSlbFastHttpProxyS 23 } 

		newSvrconn OBJECT-TYPE
		SYNTAX  CounterBasedGauge64 
		MAX-ACCESS read-only 
		STATUS current
		DESCRIPTION  "Server conn made" 
		::={ acosSlbFastHttpProxyS 24 } 

		slbFastHttpProxySnatFail OBJECT-TYPE
		SYNTAX  CounterBasedGauge64 
		MAX-ACCESS read-only 
		STATUS current
		DESCRIPTION  "Source NAT failure" 
		::={ acosSlbFastHttpProxyS 25 } 

		tcpoutrst OBJECT-TYPE
		SYNTAX  CounterBasedGauge64 
		MAX-ACCESS read-only 
		STATUS current
		DESCRIPTION  "Out RSTs" 
		::={ acosSlbFastHttpProxyS 26 } 

		fullProxy OBJECT-TYPE
		SYNTAX  CounterBasedGauge64 
		MAX-ACCESS read-only 
		STATUS current
		DESCRIPTION  "Full proxy tot" 
		::={ acosSlbFastHttpProxyS 27 } 

		fullProxyPost OBJECT-TYPE
		SYNTAX  CounterBasedGauge64 
		MAX-ACCESS read-only 
		STATUS current
		DESCRIPTION  "Full proxy POST" 
		::={ acosSlbFastHttpProxyS 28 } 

		fullProxyPipeline OBJECT-TYPE
		SYNTAX  CounterBasedGauge64 
		MAX-ACCESS read-only 
		STATUS current
		DESCRIPTION  "Full proxy pipeline" 
		::={ acosSlbFastHttpProxyS 29 } 

		fullProxyFpgaErr OBJECT-TYPE
		SYNTAX  CounterBasedGauge64 
		MAX-ACCESS read-only 
		STATUS current
		DESCRIPTION  "Full proxy fpga err" 
		::={ acosSlbFastHttpProxyS 30 } 

		reqOverLimit OBJECT-TYPE
		SYNTAX  CounterBasedGauge64 
		MAX-ACCESS read-only 
		STATUS current
		DESCRIPTION  "Request over limit" 
		::={ acosSlbFastHttpProxyS 31 } 

		reqRateOverLimit OBJECT-TYPE
		SYNTAX  CounterBasedGauge64 
		MAX-ACCESS read-only 
		STATUS current
		DESCRIPTION  "Request rate over limit" 
		::={ acosSlbFastHttpProxyS 32 } 

		l4Switching OBJECT-TYPE
		SYNTAX  CounterBasedGauge64 
		MAX-ACCESS read-only 
		STATUS current
		DESCRIPTION  "L4 switching" 
		::={ acosSlbFastHttpProxyS 33 } 

		cookieSwitching OBJECT-TYPE
		SYNTAX  CounterBasedGauge64 
		MAX-ACCESS read-only 
		STATUS current
		DESCRIPTION  "Cookie switching" 
		::={ acosSlbFastHttpProxyS 34 } 

		aflexSwitching OBJECT-TYPE
		SYNTAX  CounterBasedGauge64 
		MAX-ACCESS read-only 
		STATUS current
		DESCRIPTION  "aFleX switching" 
		::={ acosSlbFastHttpProxyS 35 } 

		httpPolicySwitching OBJECT-TYPE
		SYNTAX  CounterBasedGauge64 
		MAX-ACCESS read-only 
		STATUS current
		DESCRIPTION  "HTTP Policy switching" 
		::={ acosSlbFastHttpProxyS 36 } 

		urlSwitching OBJECT-TYPE
		SYNTAX  CounterBasedGauge64 
		MAX-ACCESS read-only 
		STATUS current
		DESCRIPTION  "URL switching" 
		::={ acosSlbFastHttpProxyS 37 } 

		hostSwitching OBJECT-TYPE
		SYNTAX  CounterBasedGauge64 
		MAX-ACCESS read-only 
		STATUS current
		DESCRIPTION  "Host switching" 
		::={ acosSlbFastHttpProxyS 38 } 

		lbSwitching OBJECT-TYPE
		SYNTAX  CounterBasedGauge64 
		MAX-ACCESS read-only 
		STATUS current
		DESCRIPTION  "Normal LB switching" 
		::={ acosSlbFastHttpProxyS 39 } 

		l4SwitchingOk OBJECT-TYPE
		SYNTAX  CounterBasedGauge64 
		MAX-ACCESS read-only 
		STATUS current
		DESCRIPTION  "L4 switching (succ)" 
		::={ acosSlbFastHttpProxyS 40 } 

		cookieSwitchingOk OBJECT-TYPE
		SYNTAX  CounterBasedGauge64 
		MAX-ACCESS read-only 
		STATUS current
		DESCRIPTION  "Cookie switching (succ)" 
		::={ acosSlbFastHttpProxyS 41 } 

		aflexSwitchingOk OBJECT-TYPE
		SYNTAX  CounterBasedGauge64 
		MAX-ACCESS read-only 
		STATUS current
		DESCRIPTION  "aFleX switching (succ)" 
		::={ acosSlbFastHttpProxyS 42 } 

		httpPolicySwitchingOk OBJECT-TYPE
		SYNTAX  CounterBasedGauge64 
		MAX-ACCESS read-only 
		STATUS current
		DESCRIPTION  "HTTP Policy switching (succ)" 
		::={ acosSlbFastHttpProxyS 43 } 

		urlSwitchingOk OBJECT-TYPE
		SYNTAX  CounterBasedGauge64 
		MAX-ACCESS read-only 
		STATUS current
		DESCRIPTION  "URL switching (succ)" 
		::={ acosSlbFastHttpProxyS 44 } 

		hostSwitchingOk OBJECT-TYPE
		SYNTAX  CounterBasedGauge64 
		MAX-ACCESS read-only 
		STATUS current
		DESCRIPTION  "Host switching (succ)" 
		::={ acosSlbFastHttpProxyS 45 } 

		lbSwitchingOk OBJECT-TYPE
		SYNTAX  CounterBasedGauge64 
		MAX-ACCESS read-only 
		STATUS current
		DESCRIPTION  "Normal LB switch. (succ)" 
		::={ acosSlbFastHttpProxyS 46 } 

		l4SwitchingEnqueue OBJECT-TYPE
		SYNTAX  CounterBasedGauge64 
		MAX-ACCESS read-only 
		STATUS current
		DESCRIPTION  "L4 switching (enQ)" 
		::={ acosSlbFastHttpProxyS 47 } 

		cookieSwitchingEnqueue OBJECT-TYPE
		SYNTAX  CounterBasedGauge64 
		MAX-ACCESS read-only 
		STATUS current
		DESCRIPTION  "Cookie switching (enQ)" 
		::={ acosSlbFastHttpProxyS 48 } 

		aflexSwitchingEnqueue OBJECT-TYPE
		SYNTAX  CounterBasedGauge64 
		MAX-ACCESS read-only 
		STATUS current
		DESCRIPTION  "aFleX switching (enQ)" 
		::={ acosSlbFastHttpProxyS 49 } 

		httpPolicySwitchingEnqueue OBJECT-TYPE
		SYNTAX  CounterBasedGauge64 
		MAX-ACCESS read-only 
		STATUS current
		DESCRIPTION  "HTTP Policy switching (enQ)" 
		::={ acosSlbFastHttpProxyS 50 } 

		urlSwitchingEnqueue OBJECT-TYPE
		SYNTAX  CounterBasedGauge64 
		MAX-ACCESS read-only 
		STATUS current
		DESCRIPTION  "URL switching (enQ)" 
		::={ acosSlbFastHttpProxyS 51 } 

		hostSwitchingEnqueue OBJECT-TYPE
		SYNTAX  CounterBasedGauge64 
		MAX-ACCESS read-only 
		STATUS current
		DESCRIPTION  "Host switching (enQ)" 
		::={ acosSlbFastHttpProxyS 52 } 

		lbSwitchingEnqueue OBJECT-TYPE
		SYNTAX  CounterBasedGauge64 
		MAX-ACCESS read-only 
		STATUS current
		DESCRIPTION  "Normal LB switch. (enQ)" 
		::={ acosSlbFastHttpProxyS 53 } 

		retry503 OBJECT-TYPE
		SYNTAX  CounterBasedGauge64 
		MAX-ACCESS read-only 
		STATUS current
		DESCRIPTION  "Retry on 503" 
		::={ acosSlbFastHttpProxyS 54 } 

		aflexRetry OBJECT-TYPE
		SYNTAX  CounterBasedGauge64 
		MAX-ACCESS read-only 
		STATUS current
		DESCRIPTION  "aFleX http retry" 
		::={ acosSlbFastHttpProxyS 55 } 

		aflexLbReselect OBJECT-TYPE
		SYNTAX  CounterBasedGauge64 
		MAX-ACCESS read-only 
		STATUS current
		DESCRIPTION  "aFleX lb reselect" 
		::={ acosSlbFastHttpProxyS 56 } 

		aflexLbReselectOk OBJECT-TYPE
		SYNTAX  CounterBasedGauge64 
		MAX-ACCESS read-only 
		STATUS current
		DESCRIPTION  "aFleX lb reselect (succ)" 
		::={ acosSlbFastHttpProxyS 57 } 

		clientRstRequest OBJECT-TYPE
		SYNTAX  CounterBasedGauge64 
		MAX-ACCESS read-only 
		STATUS current
		DESCRIPTION  "Client RST - request" 
		::={ acosSlbFastHttpProxyS 58 } 

		clientRstConnecting OBJECT-TYPE
		SYNTAX  CounterBasedGauge64 
		MAX-ACCESS read-only 
		STATUS current
		DESCRIPTION  "Client RST - connecting" 
		::={ acosSlbFastHttpProxyS 59 } 

		clientRstConnected OBJECT-TYPE
		SYNTAX  CounterBasedGauge64 
		MAX-ACCESS read-only 
		STATUS current
		DESCRIPTION  "Client RST - connected" 
		::={ acosSlbFastHttpProxyS 60 } 

		clientRstResponse OBJECT-TYPE
		SYNTAX  CounterBasedGauge64 
		MAX-ACCESS read-only 
		STATUS current
		DESCRIPTION  "Client RST - response" 
		::={ acosSlbFastHttpProxyS 61 } 

		serverRstRequest OBJECT-TYPE
		SYNTAX  CounterBasedGauge64 
		MAX-ACCESS read-only 
		STATUS current
		DESCRIPTION  "Server RST - request" 
		::={ acosSlbFastHttpProxyS 62 } 

		serverRstConnecting OBJECT-TYPE
		SYNTAX  CounterBasedGauge64 
		MAX-ACCESS read-only 
		STATUS current
		DESCRIPTION  "Server RST - connecting" 
		::={ acosSlbFastHttpProxyS 63 } 

		serverRstConnected OBJECT-TYPE
		SYNTAX  CounterBasedGauge64 
		MAX-ACCESS read-only 
		STATUS current
		DESCRIPTION  "Server RST - connected" 
		::={ acosSlbFastHttpProxyS 64 } 

		serverRstResponse OBJECT-TYPE
		SYNTAX  CounterBasedGauge64 
		MAX-ACCESS read-only 
		STATUS current
		DESCRIPTION  "Server RST - response" 
		::={ acosSlbFastHttpProxyS 65 } 

		invalidHeader OBJECT-TYPE
		SYNTAX  CounterBasedGauge64 
		MAX-ACCESS read-only 
		STATUS current
		DESCRIPTION  "Invalid header" 
		::={ acosSlbFastHttpProxyS 66 } 

		tooManyHeaders OBJECT-TYPE
		SYNTAX  CounterBasedGauge64 
		MAX-ACCESS read-only 
		STATUS current
		DESCRIPTION  "Too many headers" 
		::={ acosSlbFastHttpProxyS 67 } 

		lineTooLong OBJECT-TYPE
		SYNTAX  CounterBasedGauge64 
		MAX-ACCESS read-only 
		STATUS current
		DESCRIPTION  "Line too long" 
		::={ acosSlbFastHttpProxyS 68 } 

		headerNameTooLong OBJECT-TYPE
		SYNTAX  CounterBasedGauge64 
		MAX-ACCESS read-only 
		STATUS current
		DESCRIPTION  "Header name too long" 
		::={ acosSlbFastHttpProxyS 69 } 

		wrongRespHeader OBJECT-TYPE
		SYNTAX  CounterBasedGauge64 
		MAX-ACCESS read-only 
		STATUS current
		DESCRIPTION  "Wrong response header" 
		::={ acosSlbFastHttpProxyS 70 } 

		headerInsert OBJECT-TYPE
		SYNTAX  CounterBasedGauge64 
		MAX-ACCESS read-only 
		STATUS current
		DESCRIPTION  "Header insert" 
		::={ acosSlbFastHttpProxyS 71 } 

		headerDelete OBJECT-TYPE
		SYNTAX  CounterBasedGauge64 
		MAX-ACCESS read-only 
		STATUS current
		DESCRIPTION  "Header delete" 
		::={ acosSlbFastHttpProxyS 72 } 

		insertClientIp OBJECT-TYPE
		SYNTAX  CounterBasedGauge64 
		MAX-ACCESS read-only 
		STATUS current
		DESCRIPTION  "Insert client IP" 
		::={ acosSlbFastHttpProxyS 73 } 

		negativeReqRemain OBJECT-TYPE
		SYNTAX  CounterBasedGauge64 
		MAX-ACCESS read-only 
		STATUS current
		DESCRIPTION  "Negative request remain" 
		::={ acosSlbFastHttpProxyS 74 } 

		negativeRespRemain OBJECT-TYPE
		SYNTAX  CounterBasedGauge64 
		MAX-ACCESS read-only 
		STATUS current
		DESCRIPTION  "Negative response remain" 
		::={ acosSlbFastHttpProxyS 75 } 

		largeCookie OBJECT-TYPE
		SYNTAX  CounterBasedGauge64 
		MAX-ACCESS read-only 
		STATUS current
		DESCRIPTION  "Large cookies" 
		::={ acosSlbFastHttpProxyS 76 } 

		largeCookieHeader OBJECT-TYPE
		SYNTAX  CounterBasedGauge64 
		MAX-ACCESS read-only 
		STATUS current
		DESCRIPTION  "Large cookie headers" 
		::={ acosSlbFastHttpProxyS 77 } 

		hugeCookie OBJECT-TYPE
		SYNTAX  CounterBasedGauge64 
		MAX-ACCESS read-only 
		STATUS current
		DESCRIPTION  "Huge cookies" 
		::={ acosSlbFastHttpProxyS 78 } 

		hugeCookieHeader OBJECT-TYPE
		SYNTAX  CounterBasedGauge64 
		MAX-ACCESS read-only 
		STATUS current
		DESCRIPTION  "Huge cookie headers" 
		::={ acosSlbFastHttpProxyS 79 } 

		parseCookieFail OBJECT-TYPE
		SYNTAX  CounterBasedGauge64 
		MAX-ACCESS read-only 
		STATUS current
		DESCRIPTION  "Parse cookie fail" 
		::={ acosSlbFastHttpProxyS 80 } 

		parseSetcookieFail OBJECT-TYPE
		SYNTAX  CounterBasedGauge64 
		MAX-ACCESS read-only 
		STATUS current
		DESCRIPTION  "Parse set-cookie fail" 
		::={ acosSlbFastHttpProxyS 81 } 

		asmCookieFail OBJECT-TYPE
		SYNTAX  CounterBasedGauge64 
		MAX-ACCESS read-only 
		STATUS current
		DESCRIPTION  "Assemble cookie fail" 
		::={ acosSlbFastHttpProxyS 82 } 

		asmCookieHeaderFail OBJECT-TYPE
		SYNTAX  CounterBasedGauge64 
		MAX-ACCESS read-only 
		STATUS current
		DESCRIPTION  "Asm cookie header fail" 
		::={ acosSlbFastHttpProxyS 83 } 

		asmSetcookieFail OBJECT-TYPE
		SYNTAX  CounterBasedGauge64 
		MAX-ACCESS read-only 
		STATUS current
		DESCRIPTION  "Assemble set-cookie fail" 
		::={ acosSlbFastHttpProxyS 84 } 

		asmSetcookieHeaderFail OBJECT-TYPE
		SYNTAX  CounterBasedGauge64 
		MAX-ACCESS read-only 
		STATUS current
		DESCRIPTION  "Asm set-cookie hdr fail" 
		::={ acosSlbFastHttpProxyS 85 } 

		clientReqUnexpFlag OBJECT-TYPE
		SYNTAX  CounterBasedGauge64 
		MAX-ACCESS read-only 
		STATUS current
		DESCRIPTION  "Client req unexp flags" 
		::={ acosSlbFastHttpProxyS 86 } 

		connectingFin OBJECT-TYPE
		SYNTAX  CounterBasedGauge64 
		MAX-ACCESS read-only 
		STATUS current
		DESCRIPTION  "Connecting FIN" 
		::={ acosSlbFastHttpProxyS 87 } 

		connectingFinRetrans OBJECT-TYPE
		SYNTAX  CounterBasedGauge64 
		MAX-ACCESS read-only 
		STATUS current
		DESCRIPTION  "Connecting FIN retran" 
		::={ acosSlbFastHttpProxyS 88 } 

		connectingFinOfo OBJECT-TYPE
		SYNTAX  CounterBasedGauge64 
		MAX-ACCESS read-only 
		STATUS current
		DESCRIPTION  "Connecting FIN ofo" 
		::={ acosSlbFastHttpProxyS 89 } 

		connectingRst OBJECT-TYPE
		SYNTAX  CounterBasedGauge64 
		MAX-ACCESS read-only 
		STATUS current
		DESCRIPTION  "Connecting RST" 
		::={ acosSlbFastHttpProxyS 90 } 

		connectingRstRetrans OBJECT-TYPE
		SYNTAX  CounterBasedGauge64 
		MAX-ACCESS read-only 
		STATUS current
		DESCRIPTION  "Connecting RST retran" 
		::={ acosSlbFastHttpProxyS 91 } 

		connectingRstOfo OBJECT-TYPE
		SYNTAX  CounterBasedGauge64 
		MAX-ACCESS read-only 
		STATUS current
		DESCRIPTION  "Connecting RST ofo" 
		::={ acosSlbFastHttpProxyS 92 } 

		connectingAck OBJECT-TYPE
		SYNTAX  CounterBasedGauge64 
		MAX-ACCESS read-only 
		STATUS current
		DESCRIPTION  "Connecting ACK" 
		::={ acosSlbFastHttpProxyS 93 } 

		pktsOfo OBJECT-TYPE
		SYNTAX  CounterBasedGauge64 
		MAX-ACCESS read-only 
		STATUS current
		DESCRIPTION  "Packets ofo" 
		::={ acosSlbFastHttpProxyS 94 } 

		pktsRetrans OBJECT-TYPE
		SYNTAX  CounterBasedGauge64 
		MAX-ACCESS read-only 
		STATUS current
		DESCRIPTION  "Packets retrans" 
		::={ acosSlbFastHttpProxyS 95 } 

		pktsRetransAckFinwait OBJECT-TYPE
		SYNTAX  CounterBasedGauge64 
		MAX-ACCESS read-only 
		STATUS current
		DESCRIPTION  "retrans ACK FWAIT" 
		::={ acosSlbFastHttpProxyS 96 } 

		pktsRetransFin OBJECT-TYPE
		SYNTAX  CounterBasedGauge64 
		MAX-ACCESS read-only 
		STATUS current
		DESCRIPTION  "retrans FIN" 
		::={ acosSlbFastHttpProxyS 97 } 

		pktsRetransRst OBJECT-TYPE
		SYNTAX  CounterBasedGauge64 
		MAX-ACCESS read-only 
		STATUS current
		DESCRIPTION  "retrans RST" 
		::={ acosSlbFastHttpProxyS 98 } 

		pktsRetransPush OBJECT-TYPE
		SYNTAX  CounterBasedGauge64 
		MAX-ACCESS read-only 
		STATUS current
		DESCRIPTION  "retrans PSH" 
		::={ acosSlbFastHttpProxyS 99 } 

		staleSess OBJECT-TYPE
		SYNTAX  CounterBasedGauge64 
		MAX-ACCESS read-only 
		STATUS current
		DESCRIPTION  "Stale sess" 
		::={ acosSlbFastHttpProxyS 100 } 

		serverReselFailed OBJECT-TYPE
		SYNTAX  CounterBasedGauge64 
		MAX-ACCESS read-only 
		STATUS current
		DESCRIPTION  "Server re-select failed" 
		::={ acosSlbFastHttpProxyS 101 } 

		compressionBefore OBJECT-TYPE
		SYNTAX  CounterBasedGauge64 
		MAX-ACCESS read-only 
		STATUS current
		DESCRIPTION  "Tot data before compress" 
		::={ acosSlbFastHttpProxyS 102 } 

		compressionAfter OBJECT-TYPE
		SYNTAX  CounterBasedGauge64 
		MAX-ACCESS read-only 
		STATUS current
		DESCRIPTION  "Tot data after compress" 
		::={ acosSlbFastHttpProxyS 104 } 

		response1xx OBJECT-TYPE
		SYNTAX  CounterBasedGauge64 
		MAX-ACCESS read-only 
		STATUS current
		DESCRIPTION  "Status code 1XX" 
		::={ acosSlbFastHttpProxyS 106 } 

		response100 OBJECT-TYPE
		SYNTAX  CounterBasedGauge64 
		MAX-ACCESS read-only 
		STATUS current
		DESCRIPTION  "Status code 100" 
		::={ acosSlbFastHttpProxyS 107 } 

		response101 OBJECT-TYPE
		SYNTAX  CounterBasedGauge64 
		MAX-ACCESS read-only 
		STATUS current
		DESCRIPTION  "Status code 101" 
		::={ acosSlbFastHttpProxyS 108 } 

		response102 OBJECT-TYPE
		SYNTAX  CounterBasedGauge64 
		MAX-ACCESS read-only 
		STATUS current
		DESCRIPTION  "Status code 102" 
		::={ acosSlbFastHttpProxyS 109 } 

		response2xx OBJECT-TYPE
		SYNTAX  CounterBasedGauge64 
		MAX-ACCESS read-only 
		STATUS current
		DESCRIPTION  "Status code 2XX" 
		::={ acosSlbFastHttpProxyS 110 } 

		response200 OBJECT-TYPE
		SYNTAX  CounterBasedGauge64 
		MAX-ACCESS read-only 
		STATUS current
		DESCRIPTION  "Status code 200" 
		::={ acosSlbFastHttpProxyS 111 } 

		response201 OBJECT-TYPE
		SYNTAX  CounterBasedGauge64 
		MAX-ACCESS read-only 
		STATUS current
		DESCRIPTION  "Status code 201" 
		::={ acosSlbFastHttpProxyS 112 } 

		response202 OBJECT-TYPE
		SYNTAX  CounterBasedGauge64 
		MAX-ACCESS read-only 
		STATUS current
		DESCRIPTION  "Status code 202" 
		::={ acosSlbFastHttpProxyS 113 } 

		response203 OBJECT-TYPE
		SYNTAX  CounterBasedGauge64 
		MAX-ACCESS read-only 
		STATUS current
		DESCRIPTION  "Status code 203" 
		::={ acosSlbFastHttpProxyS 114 } 

		response204 OBJECT-TYPE
		SYNTAX  CounterBasedGauge64 
		MAX-ACCESS read-only 
		STATUS current
		DESCRIPTION  "Status code 204" 
		::={ acosSlbFastHttpProxyS 115 } 

		response205 OBJECT-TYPE
		SYNTAX  CounterBasedGauge64 
		MAX-ACCESS read-only 
		STATUS current
		DESCRIPTION  "Status code 205" 
		::={ acosSlbFastHttpProxyS 116 } 

		response206 OBJECT-TYPE
		SYNTAX  CounterBasedGauge64 
		MAX-ACCESS read-only 
		STATUS current
		DESCRIPTION  "Status code 206" 
		::={ acosSlbFastHttpProxyS 117 } 

		response207 OBJECT-TYPE
		SYNTAX  CounterBasedGauge64 
		MAX-ACCESS read-only 
		STATUS current
		DESCRIPTION  "Status code 207" 
		::={ acosSlbFastHttpProxyS 118 } 

		response3xx OBJECT-TYPE
		SYNTAX  CounterBasedGauge64 
		MAX-ACCESS read-only 
		STATUS current
		DESCRIPTION  "Status code 3XX" 
		::={ acosSlbFastHttpProxyS 119 } 

		response300 OBJECT-TYPE
		SYNTAX  CounterBasedGauge64 
		MAX-ACCESS read-only 
		STATUS current
		DESCRIPTION  "Status code 300" 
		::={ acosSlbFastHttpProxyS 120 } 

		response301 OBJECT-TYPE
		SYNTAX  CounterBasedGauge64 
		MAX-ACCESS read-only 
		STATUS current
		DESCRIPTION  "Status code 301" 
		::={ acosSlbFastHttpProxyS 121 } 

		response302 OBJECT-TYPE
		SYNTAX  CounterBasedGauge64 
		MAX-ACCESS read-only 
		STATUS current
		DESCRIPTION  "Status code 302" 
		::={ acosSlbFastHttpProxyS 122 } 

		response303 OBJECT-TYPE
		SYNTAX  CounterBasedGauge64 
		MAX-ACCESS read-only 
		STATUS current
		DESCRIPTION  "Status code 303" 
		::={ acosSlbFastHttpProxyS 123 } 

		response304 OBJECT-TYPE
		SYNTAX  CounterBasedGauge64 
		MAX-ACCESS read-only 
		STATUS current
		DESCRIPTION  "Status code 304" 
		::={ acosSlbFastHttpProxyS 124 } 

		response305 OBJECT-TYPE
		SYNTAX  CounterBasedGauge64 
		MAX-ACCESS read-only 
		STATUS current
		DESCRIPTION  "Status code 305" 
		::={ acosSlbFastHttpProxyS 125 } 

		response306 OBJECT-TYPE
		SYNTAX  CounterBasedGauge64 
		MAX-ACCESS read-only 
		STATUS current
		DESCRIPTION  "Status code 306" 
		::={ acosSlbFastHttpProxyS 126 } 

		response307 OBJECT-TYPE
		SYNTAX  CounterBasedGauge64 
		MAX-ACCESS read-only 
		STATUS current
		DESCRIPTION  "Status code 307" 
		::={ acosSlbFastHttpProxyS 127 } 

		response4xx OBJECT-TYPE
		SYNTAX  CounterBasedGauge64 
		MAX-ACCESS read-only 
		STATUS current
		DESCRIPTION  "Status code 4XX" 
		::={ acosSlbFastHttpProxyS 128 } 

		response400 OBJECT-TYPE
		SYNTAX  CounterBasedGauge64 
		MAX-ACCESS read-only 
		STATUS current
		DESCRIPTION  "Status code 400" 
		::={ acosSlbFastHttpProxyS 129 } 

		response401 OBJECT-TYPE
		SYNTAX  CounterBasedGauge64 
		MAX-ACCESS read-only 
		STATUS current
		DESCRIPTION  "Status code 401" 
		::={ acosSlbFastHttpProxyS 130 } 

		response402 OBJECT-TYPE
		SYNTAX  CounterBasedGauge64 
		MAX-ACCESS read-only 
		STATUS current
		DESCRIPTION  "Status code 402" 
		::={ acosSlbFastHttpProxyS 131 } 

		response403 OBJECT-TYPE
		SYNTAX  CounterBasedGauge64 
		MAX-ACCESS read-only 
		STATUS current
		DESCRIPTION  "Status code 403" 
		::={ acosSlbFastHttpProxyS 132 } 

		response404 OBJECT-TYPE
		SYNTAX  CounterBasedGauge64 
		MAX-ACCESS read-only 
		STATUS current
		DESCRIPTION  "Status code 404" 
		::={ acosSlbFastHttpProxyS 133 } 

		response405 OBJECT-TYPE
		SYNTAX  CounterBasedGauge64 
		MAX-ACCESS read-only 
		STATUS current
		DESCRIPTION  "Status code 405" 
		::={ acosSlbFastHttpProxyS 134 } 

		response406 OBJECT-TYPE
		SYNTAX  CounterBasedGauge64 
		MAX-ACCESS read-only 
		STATUS current
		DESCRIPTION  "Status code 406" 
		::={ acosSlbFastHttpProxyS 135 } 

		response407 OBJECT-TYPE
		SYNTAX  CounterBasedGauge64 
		MAX-ACCESS read-only 
		STATUS current
		DESCRIPTION  "Status code 407" 
		::={ acosSlbFastHttpProxyS 136 } 

		response408 OBJECT-TYPE
		SYNTAX  CounterBasedGauge64 
		MAX-ACCESS read-only 
		STATUS current
		DESCRIPTION  "Status code 408" 
		::={ acosSlbFastHttpProxyS 137 } 

		response409 OBJECT-TYPE
		SYNTAX  CounterBasedGauge64 
		MAX-ACCESS read-only 
		STATUS current
		DESCRIPTION  "Status code 409" 
		::={ acosSlbFastHttpProxyS 138 } 

		response410 OBJECT-TYPE
		SYNTAX  CounterBasedGauge64 
		MAX-ACCESS read-only 
		STATUS current
		DESCRIPTION  "Status code 410" 
		::={ acosSlbFastHttpProxyS 139 } 

		response411 OBJECT-TYPE
		SYNTAX  CounterBasedGauge64 
		MAX-ACCESS read-only 
		STATUS current
		DESCRIPTION  "Status code 411" 
		::={ acosSlbFastHttpProxyS 140 } 

		response412 OBJECT-TYPE
		SYNTAX  CounterBasedGauge64 
		MAX-ACCESS read-only 
		STATUS current
		DESCRIPTION  "Status code 412" 
		::={ acosSlbFastHttpProxyS 141 } 

		response413 OBJECT-TYPE
		SYNTAX  CounterBasedGauge64 
		MAX-ACCESS read-only 
		STATUS current
		DESCRIPTION  "Status code 413" 
		::={ acosSlbFastHttpProxyS 142 } 

		response414 OBJECT-TYPE
		SYNTAX  CounterBasedGauge64 
		MAX-ACCESS read-only 
		STATUS current
		DESCRIPTION  "Status code 414" 
		::={ acosSlbFastHttpProxyS 143 } 

		response415 OBJECT-TYPE
		SYNTAX  CounterBasedGauge64 
		MAX-ACCESS read-only 
		STATUS current
		DESCRIPTION  "Status code 415" 
		::={ acosSlbFastHttpProxyS 144 } 

		response416 OBJECT-TYPE
		SYNTAX  CounterBasedGauge64 
		MAX-ACCESS read-only 
		STATUS current
		DESCRIPTION  "Status code 416" 
		::={ acosSlbFastHttpProxyS 145 } 

		response417 OBJECT-TYPE
		SYNTAX  CounterBasedGauge64 
		MAX-ACCESS read-only 
		STATUS current
		DESCRIPTION  "Status code 417" 
		::={ acosSlbFastHttpProxyS 146 } 

		response418 OBJECT-TYPE
		SYNTAX  CounterBasedGauge64 
		MAX-ACCESS read-only 
		STATUS current
		DESCRIPTION  "Status code 418" 
		::={ acosSlbFastHttpProxyS 147 } 

		response422 OBJECT-TYPE
		SYNTAX  CounterBasedGauge64 
		MAX-ACCESS read-only 
		STATUS current
		DESCRIPTION  "Status code 422" 
		::={ acosSlbFastHttpProxyS 148 } 

		response423 OBJECT-TYPE
		SYNTAX  CounterBasedGauge64 
		MAX-ACCESS read-only 
		STATUS current
		DESCRIPTION  "Status code 423" 
		::={ acosSlbFastHttpProxyS 149 } 

		response424 OBJECT-TYPE
		SYNTAX  CounterBasedGauge64 
		MAX-ACCESS read-only 
		STATUS current
		DESCRIPTION  "Status code 424" 
		::={ acosSlbFastHttpProxyS 150 } 

		response425 OBJECT-TYPE
		SYNTAX  CounterBasedGauge64 
		MAX-ACCESS read-only 
		STATUS current
		DESCRIPTION  "Status code 425" 
		::={ acosSlbFastHttpProxyS 151 } 

		response426 OBJECT-TYPE
		SYNTAX  CounterBasedGauge64 
		MAX-ACCESS read-only 
		STATUS current
		DESCRIPTION  "Status code 426" 
		::={ acosSlbFastHttpProxyS 152 } 

		response449 OBJECT-TYPE
		SYNTAX  CounterBasedGauge64 
		MAX-ACCESS read-only 
		STATUS current
		DESCRIPTION  "Status code 449" 
		::={ acosSlbFastHttpProxyS 153 } 

		response450 OBJECT-TYPE
		SYNTAX  CounterBasedGauge64 
		MAX-ACCESS read-only 
		STATUS current
		DESCRIPTION  "Status code 450" 
		::={ acosSlbFastHttpProxyS 154 } 

		response5xx OBJECT-TYPE
		SYNTAX  CounterBasedGauge64 
		MAX-ACCESS read-only 
		STATUS current
		DESCRIPTION  "Status code 5XX" 
		::={ acosSlbFastHttpProxyS 155 } 

		response500 OBJECT-TYPE
		SYNTAX  CounterBasedGauge64 
		MAX-ACCESS read-only 
		STATUS current
		DESCRIPTION  "Status code 500" 
		::={ acosSlbFastHttpProxyS 156 } 

		response501 OBJECT-TYPE
		SYNTAX  CounterBasedGauge64 
		MAX-ACCESS read-only 
		STATUS current
		DESCRIPTION  "Status code 501" 
		::={ acosSlbFastHttpProxyS 157 } 

		response502 OBJECT-TYPE
		SYNTAX  CounterBasedGauge64 
		MAX-ACCESS read-only 
		STATUS current
		DESCRIPTION  "Status code 502" 
		::={ acosSlbFastHttpProxyS 158 } 

		response503 OBJECT-TYPE
		SYNTAX  CounterBasedGauge64 
		MAX-ACCESS read-only 
		STATUS current
		DESCRIPTION  "Status code 503" 
		::={ acosSlbFastHttpProxyS 159 } 

		response504 OBJECT-TYPE
		SYNTAX  CounterBasedGauge64 
		MAX-ACCESS read-only 
		STATUS current
		DESCRIPTION  "Status code 504" 
		::={ acosSlbFastHttpProxyS 160 } 

		response505 OBJECT-TYPE
		SYNTAX  CounterBasedGauge64 
		MAX-ACCESS read-only 
		STATUS current
		DESCRIPTION  "Status code 505" 
		::={ acosSlbFastHttpProxyS 161 } 

		response506 OBJECT-TYPE
		SYNTAX  CounterBasedGauge64 
		MAX-ACCESS read-only 
		STATUS current
		DESCRIPTION  "Status code 506" 
		::={ acosSlbFastHttpProxyS 162 } 

		response507 OBJECT-TYPE
		SYNTAX  CounterBasedGauge64 
		MAX-ACCESS read-only 
		STATUS current
		DESCRIPTION  "Status code 507" 
		::={ acosSlbFastHttpProxyS 163 } 

		response508 OBJECT-TYPE
		SYNTAX  CounterBasedGauge64 
		MAX-ACCESS read-only 
		STATUS current
		DESCRIPTION  "Status code 508" 
		::={ acosSlbFastHttpProxyS 164 } 

		response509 OBJECT-TYPE
		SYNTAX  CounterBasedGauge64 
		MAX-ACCESS read-only 
		STATUS current
		DESCRIPTION  "Status code 509" 
		::={ acosSlbFastHttpProxyS 165 } 

		response510 OBJECT-TYPE
		SYNTAX  CounterBasedGauge64 
		MAX-ACCESS read-only 
		STATUS current
		DESCRIPTION  "Status code 510" 
		::={ acosSlbFastHttpProxyS 166 } 

		response6xx OBJECT-TYPE
		SYNTAX  CounterBasedGauge64 
		MAX-ACCESS read-only 
		STATUS current
		DESCRIPTION  "Status code 6XX" 
		::={ acosSlbFastHttpProxyS 167 } 

		responseUnknown OBJECT-TYPE
		SYNTAX  CounterBasedGauge64 
		MAX-ACCESS read-only 
		STATUS current
		DESCRIPTION  "Status code unknown" 
		::={ acosSlbFastHttpProxyS 168 } 

		reqHttp10 OBJECT-TYPE
		SYNTAX  CounterBasedGauge64 
		MAX-ACCESS read-only 
		STATUS current
		DESCRIPTION  "Request 1.0" 
		::={ acosSlbFastHttpProxyS 169 } 

		reqHttp11 OBJECT-TYPE
		SYNTAX  CounterBasedGauge64 
		MAX-ACCESS read-only 
		STATUS current
		DESCRIPTION  "Request 1.1" 
		::={ acosSlbFastHttpProxyS 170 } 

		responseHttp10 OBJECT-TYPE
		SYNTAX  CounterBasedGauge64 
		MAX-ACCESS read-only 
		STATUS current
		DESCRIPTION  "Resp 1.0" 
		::={ acosSlbFastHttpProxyS 171 } 

		responseHttp11 OBJECT-TYPE
		SYNTAX  CounterBasedGauge64 
		MAX-ACCESS read-only 
		STATUS current
		DESCRIPTION  "Resp 1.1" 
		::={ acosSlbFastHttpProxyS 172 } 

		reqGet OBJECT-TYPE
		SYNTAX  CounterBasedGauge64 
		MAX-ACCESS read-only 
		STATUS current
		DESCRIPTION  "Method GET" 
		::={ acosSlbFastHttpProxyS 173 } 

		reqHead OBJECT-TYPE
		SYNTAX  CounterBasedGauge64 
		MAX-ACCESS read-only 
		STATUS current
		DESCRIPTION  "Method HEAD" 
		::={ acosSlbFastHttpProxyS 174 } 

		reqPut OBJECT-TYPE
		SYNTAX  CounterBasedGauge64 
		MAX-ACCESS read-only 
		STATUS current
		DESCRIPTION  "Method PUT" 
		::={ acosSlbFastHttpProxyS 175 } 

		reqPost OBJECT-TYPE
		SYNTAX  CounterBasedGauge64 
		MAX-ACCESS read-only 
		STATUS current
		DESCRIPTION  "Method POST" 
		::={ acosSlbFastHttpProxyS 176 } 

		reqTrace OBJECT-TYPE
		SYNTAX  CounterBasedGauge64 
		MAX-ACCESS read-only 
		STATUS current
		DESCRIPTION  "Method TRACE" 
		::={ acosSlbFastHttpProxyS 177 } 

		reqOptions OBJECT-TYPE
		SYNTAX  CounterBasedGauge64 
		MAX-ACCESS read-only 
		STATUS current
		DESCRIPTION  "Method OPTIONS" 
		::={ acosSlbFastHttpProxyS 178 } 

		reqConnect OBJECT-TYPE
		SYNTAX  CounterBasedGauge64 
		MAX-ACCESS read-only 
		STATUS current
		DESCRIPTION  "Method CONNECT" 
		::={ acosSlbFastHttpProxyS 179 } 

		reqDelete OBJECT-TYPE
		SYNTAX  CounterBasedGauge64 
		MAX-ACCESS read-only 
		STATUS current
		DESCRIPTION  "Method DELETE" 
		::={ acosSlbFastHttpProxyS 180 } 

		reqUnknown OBJECT-TYPE
		SYNTAX  CounterBasedGauge64 
		MAX-ACCESS read-only 
		STATUS current
		DESCRIPTION  "Method UNKNOWN" 
		::={ acosSlbFastHttpProxyS 181 } 

		reqContentLen OBJECT-TYPE
		SYNTAX  CounterBasedGauge64 
		MAX-ACCESS read-only 
		STATUS current
		DESCRIPTION  "Req content len" 
		::={ acosSlbFastHttpProxyS 182 } 

		rspContentLen OBJECT-TYPE
		SYNTAX  CounterBasedGauge64 
		MAX-ACCESS read-only 
		STATUS current
		DESCRIPTION  "Resp content len" 
		::={ acosSlbFastHttpProxyS 183 } 

		rspChunk OBJECT-TYPE
		SYNTAX  CounterBasedGauge64 
		MAX-ACCESS read-only 
		STATUS current
		DESCRIPTION  "Resp chunk encoding" 
		::={ acosSlbFastHttpProxyS 184 } 

		reqChunk OBJECT-TYPE
		SYNTAX  CounterBasedGauge64 
		MAX-ACCESS read-only 
		STATUS current
		DESCRIPTION  "Req chunk encoding" 
		::={ acosSlbFastHttpProxyS 185 } 

		compressRsp OBJECT-TYPE
		SYNTAX  CounterBasedGauge64 
		MAX-ACCESS read-only 
		STATUS current
		DESCRIPTION  "Compress req" 
		::={ acosSlbFastHttpProxyS 186 } 

		compressDelAcceptEnc OBJECT-TYPE
		SYNTAX  CounterBasedGauge64 
		MAX-ACCESS read-only 
		STATUS current
		DESCRIPTION  "Compress del accept enc" 
		::={ acosSlbFastHttpProxyS 187 } 

		compressRespAlreadyCompressed OBJECT-TYPE
		SYNTAX  CounterBasedGauge64 
		MAX-ACCESS read-only 
		STATUS current
		DESCRIPTION  "Resp already compressed" 
		::={ acosSlbFastHttpProxyS 188 } 

		compressContentTypeExcluded OBJECT-TYPE
		SYNTAX  CounterBasedGauge64 
		MAX-ACCESS read-only 
		STATUS current
		DESCRIPTION  "Compress cont type excl" 
		::={ acosSlbFastHttpProxyS 189 } 

		compressNoContentType OBJECT-TYPE
		SYNTAX  CounterBasedGauge64 
		MAX-ACCESS read-only 
		STATUS current
		DESCRIPTION  "Compress no cont type" 
		::={ acosSlbFastHttpProxyS 190 } 

		compressRespLtMin OBJECT-TYPE
		SYNTAX  CounterBasedGauge64 
		MAX-ACCESS read-only 
		STATUS current
		DESCRIPTION  "Compress resp less than min" 
		::={ acosSlbFastHttpProxyS 191 } 

		compressRespNoClOrCe OBJECT-TYPE
		SYNTAX  CounterBasedGauge64 
		MAX-ACCESS read-only 
		STATUS current
		DESCRIPTION  "Compress resp no CL/CE" 
		::={ acosSlbFastHttpProxyS 192 } 

		compressRatioTooHigh OBJECT-TYPE
		SYNTAX  CounterBasedGauge64 
		MAX-ACCESS read-only 
		STATUS current
		DESCRIPTION  "Compress ratio too high" 
		::={ acosSlbFastHttpProxyS 193 } 

		cacheRsp OBJECT-TYPE
		SYNTAX  CounterBasedGauge64 
		MAX-ACCESS read-only 
		STATUS current
		DESCRIPTION  "HTTP req (cache succ)" 
		::={ acosSlbFastHttpProxyS 194 } 

		closeOnDdos OBJECT-TYPE
		SYNTAX  CounterBasedGauge64 
		MAX-ACCESS read-only 
		STATUS current
		DESCRIPTION  "Close on DDoS" 
		::={ acosSlbFastHttpProxyS 195 } 

		reqHttp10Keepalive OBJECT-TYPE
		SYNTAX  CounterBasedGauge64 
		MAX-ACCESS read-only 
		STATUS current
		DESCRIPTION  "1.0 Keepalive" 
		::={ acosSlbFastHttpProxyS 196 } 

		reqSz1k OBJECT-TYPE
		SYNTAX  CounterBasedGauge64 
		MAX-ACCESS read-only 
		STATUS current
		DESCRIPTION  "Req less than equal to 1K" 
		::={ acosSlbFastHttpProxyS 197 } 

		reqSz2k OBJECT-TYPE
		SYNTAX  CounterBasedGauge64 
		MAX-ACCESS read-only 
		STATUS current
		DESCRIPTION  "Req less than equal to 2K" 
		::={ acosSlbFastHttpProxyS 198 } 

		reqSz4k OBJECT-TYPE
		SYNTAX  CounterBasedGauge64 
		MAX-ACCESS read-only 
		STATUS current
		DESCRIPTION  "Req less than equal to 4K" 
		::={ acosSlbFastHttpProxyS 199 } 

		reqSz8k OBJECT-TYPE
		SYNTAX  CounterBasedGauge64 
		MAX-ACCESS read-only 
		STATUS current
		DESCRIPTION  "Req less than equal to 8K" 
		::={ acosSlbFastHttpProxyS 200 } 

		reqSz16k OBJECT-TYPE
		SYNTAX  CounterBasedGauge64 
		MAX-ACCESS read-only 
		STATUS current
		DESCRIPTION  "Req less than equal to 16K" 
		::={ acosSlbFastHttpProxyS 201 } 

		reqSz32k OBJECT-TYPE
		SYNTAX  CounterBasedGauge64 
		MAX-ACCESS read-only 
		STATUS current
		DESCRIPTION  "Req less than equal to 32K" 
		::={ acosSlbFastHttpProxyS 202 } 

		reqSz64k OBJECT-TYPE
		SYNTAX  CounterBasedGauge64 
		MAX-ACCESS read-only 
		STATUS current
		DESCRIPTION  "Req less than equal to 64K" 
		::={ acosSlbFastHttpProxyS 203 } 

		reqSz256k OBJECT-TYPE
		SYNTAX  CounterBasedGauge64 
		MAX-ACCESS read-only 
		STATUS current
		DESCRIPTION  "Req less than equal to 256K" 
		::={ acosSlbFastHttpProxyS 204 } 

		reqSzGt256k OBJECT-TYPE
		SYNTAX  CounterBasedGauge64 
		MAX-ACCESS read-only 
		STATUS current
		DESCRIPTION  "Req greater than 256K" 
		::={ acosSlbFastHttpProxyS 205 } 

		rspSz1k OBJECT-TYPE
		SYNTAX  CounterBasedGauge64 
		MAX-ACCESS read-only 
		STATUS current
		DESCRIPTION  "Resp less than equal to 1K" 
		::={ acosSlbFastHttpProxyS 206 } 

		rspSz2k OBJECT-TYPE
		SYNTAX  CounterBasedGauge64 
		MAX-ACCESS read-only 
		STATUS current
		DESCRIPTION  "Resp less than equal to 2K" 
		::={ acosSlbFastHttpProxyS 207 } 

		rspSz4k OBJECT-TYPE
		SYNTAX  CounterBasedGauge64 
		MAX-ACCESS read-only 
		STATUS current
		DESCRIPTION  "Resp less than equal to 4K" 
		::={ acosSlbFastHttpProxyS 208 } 

		rspSz8k OBJECT-TYPE
		SYNTAX  CounterBasedGauge64 
		MAX-ACCESS read-only 
		STATUS current
		DESCRIPTION  "Resp less than equal to 8K" 
		::={ acosSlbFastHttpProxyS 209 } 

		rspSz16k OBJECT-TYPE
		SYNTAX  CounterBasedGauge64 
		MAX-ACCESS read-only 
		STATUS current
		DESCRIPTION  "Resp less than equal to 16K" 
		::={ acosSlbFastHttpProxyS 210 } 

		rspSz32k OBJECT-TYPE
		SYNTAX  CounterBasedGauge64 
		MAX-ACCESS read-only 
		STATUS current
		DESCRIPTION  "Resp less than equal to 32K" 
		::={ acosSlbFastHttpProxyS 211 } 

		rspSz64k OBJECT-TYPE
		SYNTAX  CounterBasedGauge64 
		MAX-ACCESS read-only 
		STATUS current
		DESCRIPTION  "Resp less than equal to 64K" 
		::={ acosSlbFastHttpProxyS 212 } 

		rspSz256k OBJECT-TYPE
		SYNTAX  CounterBasedGauge64 
		MAX-ACCESS read-only 
		STATUS current
		DESCRIPTION  "Resp less than equal to 256K" 
		::={ acosSlbFastHttpProxyS 213 } 

		rspSzGt256k OBJECT-TYPE
		SYNTAX  CounterBasedGauge64 
		MAX-ACCESS read-only 
		STATUS current
		DESCRIPTION  "Resp greater than 256K" 
		::={ acosSlbFastHttpProxyS 214 } 

		chunkSz512 OBJECT-TYPE
		SYNTAX  CounterBasedGauge64 
		MAX-ACCESS read-only 
		STATUS current
		DESCRIPTION  "Chunk less than equal to 512" 
		::={ acosSlbFastHttpProxyS 215 } 

		chunkSz1k OBJECT-TYPE
		SYNTAX  CounterBasedGauge64 
		MAX-ACCESS read-only 
		STATUS current
		DESCRIPTION  "Chunk less than equal to 1K" 
		::={ acosSlbFastHttpProxyS 216 } 

		chunkSz2k OBJECT-TYPE
		SYNTAX  CounterBasedGauge64 
		MAX-ACCESS read-only 
		STATUS current
		DESCRIPTION  "Chunk less than equal to 2K" 
		::={ acosSlbFastHttpProxyS 217 } 

		chunkSz4k OBJECT-TYPE
		SYNTAX  CounterBasedGauge64 
		MAX-ACCESS read-only 
		STATUS current
		DESCRIPTION  "Chunk less than equal to 4K" 
		::={ acosSlbFastHttpProxyS 218 } 

		chunkSzGt4k OBJECT-TYPE
		SYNTAX  CounterBasedGauge64 
		MAX-ACCESS read-only 
		STATUS current
		DESCRIPTION  "Chunk greater than 4K" 
		::={ acosSlbFastHttpProxyS 219 } 

		pconnConnecting OBJECT-TYPE
		SYNTAX  CounterBasedGauge64 
		MAX-ACCESS read-only 
		STATUS current
		DESCRIPTION  "pconn connecting" 
		::={ acosSlbFastHttpProxyS 220 } 

		pconnConnected OBJECT-TYPE
		SYNTAX  CounterBasedGauge64 
		MAX-ACCESS read-only 
		STATUS current
		DESCRIPTION  "pconn connected" 
		::={ acosSlbFastHttpProxyS 221 } 

		pconnConnectingFailed OBJECT-TYPE
		SYNTAX  CounterBasedGauge64 
		MAX-ACCESS read-only 
		STATUS current
		DESCRIPTION  "pconn conn failed" 
		::={ acosSlbFastHttpProxyS 222 } 

		chunkBad OBJECT-TYPE
		SYNTAX  CounterBasedGauge64 
		MAX-ACCESS read-only 
		STATUS current
		DESCRIPTION  "Bad Chunk" 
		::={ acosSlbFastHttpProxyS 223 } 

		req10u OBJECT-TYPE
		SYNTAX  CounterBasedGauge64 
		MAX-ACCESS read-only 
		STATUS current
		DESCRIPTION  "Rsp time less than 10u" 
		::={ acosSlbFastHttpProxyS 238 } 

		req20u OBJECT-TYPE
		SYNTAX  CounterBasedGauge64 
		MAX-ACCESS read-only 
		STATUS current
		DESCRIPTION  "Rsp time less than 20u" 
		::={ acosSlbFastHttpProxyS 239 } 

		req50u OBJECT-TYPE
		SYNTAX  CounterBasedGauge64 
		MAX-ACCESS read-only 
		STATUS current
		DESCRIPTION  "Rsp time less than 50u" 
		::={ acosSlbFastHttpProxyS 240 } 

		req100u OBJECT-TYPE
		SYNTAX  CounterBasedGauge64 
		MAX-ACCESS read-only 
		STATUS current
		DESCRIPTION  "Rsp time less than 100u" 
		::={ acosSlbFastHttpProxyS 241 } 

		req200u OBJECT-TYPE
		SYNTAX  CounterBasedGauge64 
		MAX-ACCESS read-only 
		STATUS current
		DESCRIPTION  "Rsp time less than 200u" 
		::={ acosSlbFastHttpProxyS 242 } 

		req500u OBJECT-TYPE
		SYNTAX  CounterBasedGauge64 
		MAX-ACCESS read-only 
		STATUS current
		DESCRIPTION  "Rsp time less than 500u" 
		::={ acosSlbFastHttpProxyS 243 } 

		req1m OBJECT-TYPE
		SYNTAX  CounterBasedGauge64 
		MAX-ACCESS read-only 
		STATUS current
		DESCRIPTION  "Rsp time less than 1m" 
		::={ acosSlbFastHttpProxyS 244 } 

		req2m OBJECT-TYPE
		SYNTAX  CounterBasedGauge64 
		MAX-ACCESS read-only 
		STATUS current
		DESCRIPTION  "Rsp time less than 2m" 
		::={ acosSlbFastHttpProxyS 245 } 

		req5m OBJECT-TYPE
		SYNTAX  CounterBasedGauge64 
		MAX-ACCESS read-only 
		STATUS current
		DESCRIPTION  "Rsp time less than 5m" 
		::={ acosSlbFastHttpProxyS 246 } 

		req10m OBJECT-TYPE
		SYNTAX  CounterBasedGauge64 
		MAX-ACCESS read-only 
		STATUS current
		DESCRIPTION  "Rsp time less than 10m" 
		::={ acosSlbFastHttpProxyS 247 } 

		req20m OBJECT-TYPE
		SYNTAX  CounterBasedGauge64 
		MAX-ACCESS read-only 
		STATUS current
		DESCRIPTION  "Rsp time less than 20m" 
		::={ acosSlbFastHttpProxyS 248 } 

		req50m OBJECT-TYPE
		SYNTAX  CounterBasedGauge64 
		MAX-ACCESS read-only 
		STATUS current
		DESCRIPTION  "Rsp time less than 50m" 
		::={ acosSlbFastHttpProxyS 249 } 

		req100m OBJECT-TYPE
		SYNTAX  CounterBasedGauge64 
		MAX-ACCESS read-only 
		STATUS current
		DESCRIPTION  "Rsp time less than 100m" 
		::={ acosSlbFastHttpProxyS 250 } 

		req200m OBJECT-TYPE
		SYNTAX  CounterBasedGauge64 
		MAX-ACCESS read-only 
		STATUS current
		DESCRIPTION  "Rsp time less than 200m" 
		::={ acosSlbFastHttpProxyS 251 } 

		req500m OBJECT-TYPE
		SYNTAX  CounterBasedGauge64 
		MAX-ACCESS read-only 
		STATUS current
		DESCRIPTION  "Rsp time less than 500m" 
		::={ acosSlbFastHttpProxyS 252 } 

		req1s OBJECT-TYPE
		SYNTAX  CounterBasedGauge64 
		MAX-ACCESS read-only 
		STATUS current
		DESCRIPTION  "Rsp time less than 1s" 
		::={ acosSlbFastHttpProxyS 253 } 

		req2s OBJECT-TYPE
		SYNTAX  CounterBasedGauge64 
		MAX-ACCESS read-only 
		STATUS current
		DESCRIPTION  "Rsp time less than 2s" 
		::={ acosSlbFastHttpProxyS 254 } 

		req5s OBJECT-TYPE
		SYNTAX  CounterBasedGauge64 
		MAX-ACCESS read-only 
		STATUS current
		DESCRIPTION  "Rsp time less than 5s" 
		::={ acosSlbFastHttpProxyS 255 } 

		reqOver5s OBJECT-TYPE
		SYNTAX  CounterBasedGauge64 
		MAX-ACCESS read-only 
		STATUS current
		DESCRIPTION  "Rsp time greater than equal to 5s" 
		::={ acosSlbFastHttpProxyS 256 } 

		insertClientPort OBJECT-TYPE
		SYNTAX  CounterBasedGauge64 
		MAX-ACCESS read-only 
		STATUS current
		DESCRIPTION  "Insert client Port" 
		::={ acosSlbFastHttpProxyS 257 } 

		reqTrack OBJECT-TYPE
		SYNTAX  CounterBasedGauge64 
		MAX-ACCESS read-only 
		STATUS current
		DESCRIPTION  "Method TRACK" 
		::={ acosSlbFastHttpProxyS 258 } 

		fullProxyPut OBJECT-TYPE
		SYNTAX  CounterBasedGauge64 
		MAX-ACCESS read-only 
		STATUS current
		DESCRIPTION  "Full proxy PUT" 
		::={ acosSlbFastHttpProxyS 259 } 

		nonHttpBypass OBJECT-TYPE
		SYNTAX  CounterBasedGauge64 
		MAX-ACCESS read-only 
		STATUS current
		DESCRIPTION  "Non-HTTP bypass" 
		::={ acosSlbFastHttpProxyS 260 } 

		skipInsertClientIp OBJECT-TYPE
		SYNTAX  CounterBasedGauge64 
		MAX-ACCESS read-only 
		STATUS current
		DESCRIPTION  "Skip Insert Client IP" 
		::={ acosSlbFastHttpProxyS 261 } 

		skipInsertClientPort OBJECT-TYPE
		SYNTAX  CounterBasedGauge64 
		MAX-ACCESS read-only 
		STATUS current
		DESCRIPTION  "Skip Insert Client Port" 
		::={ acosSlbFastHttpProxyS 262 } 

		decompressionBefore OBJECT-TYPE
		SYNTAX  CounterBasedGauge64 
		MAX-ACCESS read-only 
		STATUS current
		DESCRIPTION  "Tot data before decompress" 
		::={ acosSlbFastHttpProxyS 263 } 

		decompressionAfter OBJECT-TYPE
		SYNTAX  CounterBasedGauge64 
		MAX-ACCESS read-only 
		STATUS current
		DESCRIPTION  "Tot data after decompress" 
		::={ acosSlbFastHttpProxyS 264 } 

		httpPktsInSeq OBJECT-TYPE
		SYNTAX  CounterBasedGauge64 
		MAX-ACCESS read-only 
		STATUS current
		DESCRIPTION  "Tot In-seq fHTTP packets" 
		::={ acosSlbFastHttpProxyS 265 } 

		httpPktsRetx OBJECT-TYPE
		SYNTAX  CounterBasedGauge64 
		MAX-ACCESS read-only 
		STATUS current
		DESCRIPTION  "Tot Re-Tx fHTTP packets" 
		::={ acosSlbFastHttpProxyS 266 } 

		httpClientRetx OBJECT-TYPE
		SYNTAX  CounterBasedGauge64 
		MAX-ACCESS read-only 
		STATUS current
		DESCRIPTION  "Client Re-Tx fHTTP packets" 
		::={ acosSlbFastHttpProxyS 267 } 

		httpServerRetx OBJECT-TYPE
		SYNTAX  CounterBasedGauge64 
		MAX-ACCESS read-only 
		STATUS current
		DESCRIPTION  "Server Re-Tx fHTTP packets" 
		::={ acosSlbFastHttpProxyS 268 } 

		httpPktsOfo OBJECT-TYPE
		SYNTAX  CounterBasedGauge64 
		MAX-ACCESS read-only 
		STATUS current
		DESCRIPTION  "fHTTP Out of Order packets" 
		::={ acosSlbFastHttpProxyS 269 } 

acosSlbFtpProxy                     OBJECT IDENTIFIER ::= { acosSlb 50 }
acosSlbFtpProxyS                    OBJECT IDENTIFIER ::= { acosSlbFtpProxy 1 }

		num OBJECT-TYPE
		SYNTAX  CounterBasedGauge64 
		MAX-ACCESS read-only 
		STATUS current
		DESCRIPTION  "Num" 
		::={ acosSlbFtpProxyS 1 } 

		slbFtpProxyCurr OBJECT-TYPE
		SYNTAX  CounterBasedGauge64 
		MAX-ACCESS read-only 
		STATUS current
		DESCRIPTION  "Current proxy conns" 
		::={ acosSlbFtpProxyS 2 } 

		slbFtpProxyTotal OBJECT-TYPE
		SYNTAX  CounterBasedGauge64 
		MAX-ACCESS read-only 
		STATUS current
		DESCRIPTION  "Total proxy conns" 
		::={ acosSlbFtpProxyS 3 } 

		slbFtpProxySvrselFail OBJECT-TYPE
		SYNTAX  CounterBasedGauge64 
		MAX-ACCESS read-only 
		STATUS current
		DESCRIPTION  "Server selection failure" 
		::={ acosSlbFtpProxyS 4 } 

		slbFtpProxyNoRoute OBJECT-TYPE
		SYNTAX  CounterBasedGauge64 
		MAX-ACCESS read-only 
		STATUS current
		DESCRIPTION  "no route failure" 
		::={ acosSlbFtpProxyS 5 } 

		slbFtpProxySnatFail OBJECT-TYPE
		SYNTAX  CounterBasedGauge64 
		MAX-ACCESS read-only 
		STATUS current
		DESCRIPTION  "source nat failure" 
		::={ acosSlbFtpProxyS 6 } 

		feat OBJECT-TYPE
		SYNTAX  CounterBasedGauge64 
		MAX-ACCESS read-only 
		STATUS current
		DESCRIPTION  "feat packet" 
		::={ acosSlbFtpProxyS 7 } 

		cc OBJECT-TYPE
		SYNTAX  CounterBasedGauge64 
		MAX-ACCESS read-only 
		STATUS current
		DESCRIPTION  "clear ctrl port packet" 
		::={ acosSlbFtpProxyS 8 } 

		dataSsl OBJECT-TYPE
		SYNTAX  CounterBasedGauge64 
		MAX-ACCESS read-only 
		STATUS current
		DESCRIPTION  "data ssl force" 
		::={ acosSlbFtpProxyS 9 } 

		slbFtpProxyLineTooLong OBJECT-TYPE
		SYNTAX  CounterBasedGauge64 
		MAX-ACCESS read-only 
		STATUS current
		DESCRIPTION  "line too long" 
		::={ acosSlbFtpProxyS 10 } 

		lineMemFreed OBJECT-TYPE
		SYNTAX  CounterBasedGauge64 
		MAX-ACCESS read-only 
		STATUS current
		DESCRIPTION  "request line freed" 
		::={ acosSlbFtpProxyS 11 } 

		invalidStartLine OBJECT-TYPE
		SYNTAX  CounterBasedGauge64 
		MAX-ACCESS read-only 
		STATUS current
		DESCRIPTION  "invalid start line" 
		::={ acosSlbFtpProxyS 12 } 

		authTls OBJECT-TYPE
		SYNTAX  CounterBasedGauge64 
		MAX-ACCESS read-only 
		STATUS current
		DESCRIPTION  "auth tls cmd" 
		::={ acosSlbFtpProxyS 13 } 

		prot OBJECT-TYPE
		SYNTAX  CounterBasedGauge64 
		MAX-ACCESS read-only 
		STATUS current
		DESCRIPTION  "prot cmd" 
		::={ acosSlbFtpProxyS 14 } 

		pbsz OBJECT-TYPE
		SYNTAX  CounterBasedGauge64 
		MAX-ACCESS read-only 
		STATUS current
		DESCRIPTION  "pbsz cmd" 
		::={ acosSlbFtpProxyS 15 } 

		pasv OBJECT-TYPE
		SYNTAX  CounterBasedGauge64 
		MAX-ACCESS read-only 
		STATUS current
		DESCRIPTION  "pasv cmd" 
		::={ acosSlbFtpProxyS 16 } 

		slbFtpProxyPort OBJECT-TYPE
		SYNTAX  CounterBasedGauge64 
		MAX-ACCESS read-only 
		STATUS current
		DESCRIPTION  "port cmd" 
		::={ acosSlbFtpProxyS 17 } 

		requestDontCare OBJECT-TYPE
		SYNTAX  CounterBasedGauge64 
		MAX-ACCESS read-only 
		STATUS current
		DESCRIPTION  "other cmd" 
		::={ acosSlbFtpProxyS 18 } 

		clientAuthTls OBJECT-TYPE
		SYNTAX  CounterBasedGauge64 
		MAX-ACCESS read-only 
		STATUS current
		DESCRIPTION  "client auth tls" 
		::={ acosSlbFtpProxyS 19 } 

		cantFindPasv OBJECT-TYPE
		SYNTAX  CounterBasedGauge64 
		MAX-ACCESS read-only 
		STATUS current
		DESCRIPTION  "cant find pasv" 
		::={ acosSlbFtpProxyS 20 } 

		pasvAddrNeServer OBJECT-TYPE
		SYNTAX  CounterBasedGauge64 
		MAX-ACCESS read-only 
		STATUS current
		DESCRIPTION  "psv addr not equal to svr" 
		::={ acosSlbFtpProxyS 21 } 

		smpCreateFail OBJECT-TYPE
		SYNTAX  CounterBasedGauge64 
		MAX-ACCESS read-only 
		STATUS current
		DESCRIPTION  "smp create fail" 
		::={ acosSlbFtpProxyS 22 } 

		dataServerConnFail OBJECT-TYPE
		SYNTAX  CounterBasedGauge64 
		MAX-ACCESS read-only 
		STATUS current
		DESCRIPTION  "data svr conn fail" 
		::={ acosSlbFtpProxyS 23 } 

		dataSendFail OBJECT-TYPE
		SYNTAX  CounterBasedGauge64 
		MAX-ACCESS read-only 
		STATUS current
		DESCRIPTION  "data send fail" 
		::={ acosSlbFtpProxyS 24 } 

		epsv OBJECT-TYPE
		SYNTAX  CounterBasedGauge64 
		MAX-ACCESS read-only 
		STATUS current
		DESCRIPTION  "epsv command" 
		::={ acosSlbFtpProxyS 25 } 

		cantFindEpsv OBJECT-TYPE
		SYNTAX  CounterBasedGauge64 
		MAX-ACCESS read-only 
		STATUS current
		DESCRIPTION  "cant find epsv" 
		::={ acosSlbFtpProxyS 26 } 

		dataCurr OBJECT-TYPE
		SYNTAX  CounterBasedGauge64 
		MAX-ACCESS read-only 
		STATUS current
		DESCRIPTION  "Current Data Proxy" 
		::={ acosSlbFtpProxyS 27 } 

		dataTotal OBJECT-TYPE
		SYNTAX  CounterBasedGauge64 
		MAX-ACCESS read-only 
		STATUS current
		DESCRIPTION  "Total Data Proxy" 
		::={ acosSlbFtpProxyS 28 } 

		authUnsupported OBJECT-TYPE
		SYNTAX  CounterBasedGauge64 
		MAX-ACCESS read-only 
		STATUS current
		DESCRIPTION  "Unsupported auth" 
		::={ acosSlbFtpProxyS 29 } 

		adat OBJECT-TYPE
		SYNTAX  CounterBasedGauge64 
		MAX-ACCESS read-only 
		STATUS current
		DESCRIPTION  "adat cmd" 
		::={ acosSlbFtpProxyS 30 } 

		unsupportedPbszValue OBJECT-TYPE
		SYNTAX  CounterBasedGauge64 
		MAX-ACCESS read-only 
		STATUS current
		DESCRIPTION  "Unsupported PBSZ" 
		::={ acosSlbFtpProxyS 31 } 

		unsupportedProtValue OBJECT-TYPE
		SYNTAX  CounterBasedGauge64 
		MAX-ACCESS read-only 
		STATUS current
		DESCRIPTION  "Unsupported PROT" 
		::={ acosSlbFtpProxyS 32 } 

		unsupportedCommand OBJECT-TYPE
		SYNTAX  CounterBasedGauge64 
		MAX-ACCESS read-only 
		STATUS current
		DESCRIPTION  "Unsupported cmd" 
		::={ acosSlbFtpProxyS 33 } 

		controlToClear OBJECT-TYPE
		SYNTAX  CounterBasedGauge64 
		MAX-ACCESS read-only 
		STATUS current
		DESCRIPTION  "Control chn clear txt" 
		::={ acosSlbFtpProxyS 34 } 

		controlToSsl OBJECT-TYPE
		SYNTAX  CounterBasedGauge64 
		MAX-ACCESS read-only 
		STATUS current
		DESCRIPTION  "Control chn ssl" 
		::={ acosSlbFtpProxyS 35 } 

		badSequence OBJECT-TYPE
		SYNTAX  CounterBasedGauge64 
		MAX-ACCESS read-only 
		STATUS current
		DESCRIPTION  "Bad Sequence" 
		::={ acosSlbFtpProxyS 36 } 

		rsvPersistConnFail OBJECT-TYPE
		SYNTAX  CounterBasedGauge64 
		MAX-ACCESS read-only 
		STATUS current
		DESCRIPTION  "Serv Sel Persist fail" 
		::={ acosSlbFtpProxyS 37 } 

		smpV6Fail OBJECT-TYPE
		SYNTAX  CounterBasedGauge64 
		MAX-ACCESS read-only 
		STATUS current
		DESCRIPTION  "Serv Sel SMPv6 fail" 
		::={ acosSlbFtpProxyS 38 } 

		smpV4Fail OBJECT-TYPE
		SYNTAX  CounterBasedGauge64 
		MAX-ACCESS read-only 
		STATUS current
		DESCRIPTION  "Serv Sel SMPv4 fail" 
		::={ acosSlbFtpProxyS 39 } 

		insertTupleFail OBJECT-TYPE
		SYNTAX  CounterBasedGauge64 
		MAX-ACCESS read-only 
		STATUS current
		DESCRIPTION  "Serv Sel insert tuple fail" 
		::={ acosSlbFtpProxyS 40 } 

		clEstErr OBJECT-TYPE
		SYNTAX  CounterBasedGauge64 
		MAX-ACCESS read-only 
		STATUS current
		DESCRIPTION  "Client EST state erro" 
		::={ acosSlbFtpProxyS 41 } 

		serConnectingErr OBJECT-TYPE
		SYNTAX  CounterBasedGauge64 
		MAX-ACCESS read-only 
		STATUS current
		DESCRIPTION  "Serv CTNG state error" 
		::={ acosSlbFtpProxyS 42 } 

		serverResponseErr OBJECT-TYPE
		SYNTAX  CounterBasedGauge64 
		MAX-ACCESS read-only 
		STATUS current
		DESCRIPTION  "Serv RESP state error" 
		::={ acosSlbFtpProxyS 43 } 

		clRequestErr OBJECT-TYPE
		SYNTAX  CounterBasedGauge64 
		MAX-ACCESS read-only 
		STATUS current
		DESCRIPTION  "Client RQ state error" 
		::={ acosSlbFtpProxyS 44 } 

		dataConnStartErr OBJECT-TYPE
		SYNTAX  CounterBasedGauge64 
		MAX-ACCESS read-only 
		STATUS current
		DESCRIPTION  "Data Start state error" 
		::={ acosSlbFtpProxyS 45 } 

		dataServConnectingErr OBJECT-TYPE
		SYNTAX  CounterBasedGauge64 
		MAX-ACCESS read-only 
		STATUS current
		DESCRIPTION  "Data Serv CTNG error" 
		::={ acosSlbFtpProxyS 46 } 

		dataServConnectedErr OBJECT-TYPE
		SYNTAX  CounterBasedGauge64 
		MAX-ACCESS read-only 
		STATUS current
		DESCRIPTION  "Data Serv CTED error" 
		::={ acosSlbFtpProxyS 47 } 

		request OBJECT-TYPE
		SYNTAX  CounterBasedGauge64 
		MAX-ACCESS read-only 
		STATUS current
		DESCRIPTION  "Total FTP Request" 
		::={ acosSlbFtpProxyS 48 } 

		authReq OBJECT-TYPE
		SYNTAX  CounterBasedGauge64 
		MAX-ACCESS read-only 
		STATUS current
		DESCRIPTION  "Auth Request" 
		::={ acosSlbFtpProxyS 49 } 

		authSucc OBJECT-TYPE
		SYNTAX  CounterBasedGauge64 
		MAX-ACCESS read-only 
		STATUS current
		DESCRIPTION  "Auth Success" 
		::={ acosSlbFtpProxyS 50 } 

		authFail OBJECT-TYPE
		SYNTAX  CounterBasedGauge64 
		MAX-ACCESS read-only 
		STATUS current
		DESCRIPTION  "Auth Failure" 
		::={ acosSlbFtpProxyS 51 } 

		fwdToInternet OBJECT-TYPE
		SYNTAX  CounterBasedGauge64 
		MAX-ACCESS read-only 
		STATUS current
		DESCRIPTION  "Forward to Internet" 
		::={ acosSlbFtpProxyS 52 } 

		fwdToSg OBJECT-TYPE
		SYNTAX  CounterBasedGauge64 
		MAX-ACCESS read-only 
		STATUS current
		DESCRIPTION  "Total Forward to Service-group" 
		::={ acosSlbFtpProxyS 53 } 

		drop OBJECT-TYPE
		SYNTAX  CounterBasedGauge64 
		MAX-ACCESS read-only 
		STATUS current
		DESCRIPTION  "Total FTP Drop" 
		::={ acosSlbFtpProxyS 54 } 

		dsSucc OBJECT-TYPE
		SYNTAX  CounterBasedGauge64 
		MAX-ACCESS read-only 
		STATUS current
		DESCRIPTION  "Host Domain Name is resolved" 
		::={ acosSlbFtpProxyS 55 } 

		dsFail OBJECT-TYPE
		SYNTAX  CounterBasedGauge64 
		MAX-ACCESS read-only 
		STATUS current
		DESCRIPTION  "Host Domain Name isn't resolved" 
		::={ acosSlbFtpProxyS 56 } 

		open OBJECT-TYPE
		SYNTAX  CounterBasedGauge64 
		MAX-ACCESS read-only 
		STATUS current
		DESCRIPTION  "open cmd" 
		::={ acosSlbFtpProxyS 57 } 

		site OBJECT-TYPE
		SYNTAX  CounterBasedGauge64 
		MAX-ACCESS read-only 
		STATUS current
		DESCRIPTION  "site cmd" 
		::={ acosSlbFtpProxyS 58 } 

		user OBJECT-TYPE
		SYNTAX  CounterBasedGauge64 
		MAX-ACCESS read-only 
		STATUS current
		DESCRIPTION  "user cmd" 
		::={ acosSlbFtpProxyS 59 } 

		pass OBJECT-TYPE
		SYNTAX  CounterBasedGauge64 
		MAX-ACCESS read-only 
		STATUS current
		DESCRIPTION  "pass cmd" 
		::={ acosSlbFtpProxyS 60 } 

		quit OBJECT-TYPE
		SYNTAX  CounterBasedGauge64 
		MAX-ACCESS read-only 
		STATUS current
		DESCRIPTION  "quit cmd" 
		::={ acosSlbFtpProxyS 61 } 

		eprt OBJECT-TYPE
		SYNTAX  CounterBasedGauge64 
		MAX-ACCESS read-only 
		STATUS current
		DESCRIPTION  "eprt cmd" 
		::={ acosSlbFtpProxyS 62 } 

		cantFindPort OBJECT-TYPE
		SYNTAX  CounterBasedGauge64 
		MAX-ACCESS read-only 
		STATUS current
		DESCRIPTION  "cant find port" 
		::={ acosSlbFtpProxyS 63 } 

		cantFindEprt OBJECT-TYPE
		SYNTAX  CounterBasedGauge64 
		MAX-ACCESS read-only 
		STATUS current
		DESCRIPTION  "cant find eprt" 
		::={ acosSlbFtpProxyS 64 } 

acosSlbImapProxy                    OBJECT IDENTIFIER ::= { acosSlb 51 }
acosSlbImapProxyS                   OBJECT IDENTIFIER ::= { acosSlbImapProxy 1 }

		num OBJECT-TYPE
		SYNTAX  CounterBasedGauge64 
		MAX-ACCESS read-only 
		STATUS current
		DESCRIPTION  "Num" 
		::={ acosSlbImapProxyS 1 } 

		curr OBJECT-TYPE
		SYNTAX  CounterBasedGauge64 
		MAX-ACCESS read-only 
		STATUS current
		DESCRIPTION  "Current proxy conns" 
		::={ acosSlbImapProxyS 2 } 

		total OBJECT-TYPE
		SYNTAX  CounterBasedGauge64 
		MAX-ACCESS read-only 
		STATUS current
		DESCRIPTION  "Total proxy conns" 
		::={ acosSlbImapProxyS 3 } 

		svrselFail OBJECT-TYPE
		SYNTAX  CounterBasedGauge64 
		MAX-ACCESS read-only 
		STATUS current
		DESCRIPTION  "Server selection failure" 
		::={ acosSlbImapProxyS 4 } 

		noRoute OBJECT-TYPE
		SYNTAX  CounterBasedGauge64 
		MAX-ACCESS read-only 
		STATUS current
		DESCRIPTION  "no route failure" 
		::={ acosSlbImapProxyS 5 } 

		snatFail OBJECT-TYPE
		SYNTAX  CounterBasedGauge64 
		MAX-ACCESS read-only 
		STATUS current
		DESCRIPTION  "source nat failure" 
		::={ acosSlbImapProxyS 6 } 

		feat OBJECT-TYPE
		SYNTAX  CounterBasedGauge64 
		MAX-ACCESS read-only 
		STATUS current
		DESCRIPTION  "feat packet" 
		::={ acosSlbImapProxyS 7 } 

		cc OBJECT-TYPE
		SYNTAX  CounterBasedGauge64 
		MAX-ACCESS read-only 
		STATUS current
		DESCRIPTION  "clear ctrl port packet" 
		::={ acosSlbImapProxyS 8 } 

		dataSsl OBJECT-TYPE
		SYNTAX  CounterBasedGauge64 
		MAX-ACCESS read-only 
		STATUS current
		DESCRIPTION  "data ssl force" 
		::={ acosSlbImapProxyS 9 } 

		lineTooLong OBJECT-TYPE
		SYNTAX  CounterBasedGauge64 
		MAX-ACCESS read-only 
		STATUS current
		DESCRIPTION  "line too long" 
		::={ acosSlbImapProxyS 10 } 

		lineMemFreed OBJECT-TYPE
		SYNTAX  CounterBasedGauge64 
		MAX-ACCESS read-only 
		STATUS current
		DESCRIPTION  "request line freed" 
		::={ acosSlbImapProxyS 11 } 

		invalidStartLine OBJECT-TYPE
		SYNTAX  CounterBasedGauge64 
		MAX-ACCESS read-only 
		STATUS current
		DESCRIPTION  "invalid start line" 
		::={ acosSlbImapProxyS 12 } 

		authTls OBJECT-TYPE
		SYNTAX  CounterBasedGauge64 
		MAX-ACCESS read-only 
		STATUS current
		DESCRIPTION  "auth tls cmd" 
		::={ acosSlbImapProxyS 13 } 

		prot OBJECT-TYPE
		SYNTAX  CounterBasedGauge64 
		MAX-ACCESS read-only 
		STATUS current
		DESCRIPTION  "prot cmd" 
		::={ acosSlbImapProxyS 14 } 

		pbsz OBJECT-TYPE
		SYNTAX  CounterBasedGauge64 
		MAX-ACCESS read-only 
		STATUS current
		DESCRIPTION  "pbsz cmd" 
		::={ acosSlbImapProxyS 15 } 

		pasv OBJECT-TYPE
		SYNTAX  CounterBasedGauge64 
		MAX-ACCESS read-only 
		STATUS current
		DESCRIPTION  "pasv cmd" 
		::={ acosSlbImapProxyS 16 } 

		port OBJECT-TYPE
		SYNTAX  CounterBasedGauge64 
		MAX-ACCESS read-only 
		STATUS current
		DESCRIPTION  "port cmd" 
		::={ acosSlbImapProxyS 17 } 

		requestDontCare OBJECT-TYPE
		SYNTAX  CounterBasedGauge64 
		MAX-ACCESS read-only 
		STATUS current
		DESCRIPTION  "other cmd" 
		::={ acosSlbImapProxyS 18 } 

		clientAuthTls OBJECT-TYPE
		SYNTAX  CounterBasedGauge64 
		MAX-ACCESS read-only 
		STATUS current
		DESCRIPTION  "client auth tls" 
		::={ acosSlbImapProxyS 19 } 

		cantFindPasv OBJECT-TYPE
		SYNTAX  CounterBasedGauge64 
		MAX-ACCESS read-only 
		STATUS current
		DESCRIPTION  "cant find pasv" 
		::={ acosSlbImapProxyS 20 } 

		pasvAddrNeServer OBJECT-TYPE
		SYNTAX  CounterBasedGauge64 
		MAX-ACCESS read-only 
		STATUS current
		DESCRIPTION  "psv addr not equal to svr" 
		::={ acosSlbImapProxyS 21 } 

		smpCreateFail OBJECT-TYPE
		SYNTAX  CounterBasedGauge64 
		MAX-ACCESS read-only 
		STATUS current
		DESCRIPTION  "smp create fail" 
		::={ acosSlbImapProxyS 22 } 

		dataServerConnFail OBJECT-TYPE
		SYNTAX  CounterBasedGauge64 
		MAX-ACCESS read-only 
		STATUS current
		DESCRIPTION  "data svr conn fail" 
		::={ acosSlbImapProxyS 23 } 

		dataSendFail OBJECT-TYPE
		SYNTAX  CounterBasedGauge64 
		MAX-ACCESS read-only 
		STATUS current
		DESCRIPTION  "data send fail" 
		::={ acosSlbImapProxyS 24 } 

		epsv OBJECT-TYPE
		SYNTAX  CounterBasedGauge64 
		MAX-ACCESS read-only 
		STATUS current
		DESCRIPTION  "epsv command" 
		::={ acosSlbImapProxyS 25 } 

		cantFindEpsv OBJECT-TYPE
		SYNTAX  CounterBasedGauge64 
		MAX-ACCESS read-only 
		STATUS current
		DESCRIPTION  "cant find epsv" 
		::={ acosSlbImapProxyS 26 } 

		dataCurr OBJECT-TYPE
		SYNTAX  CounterBasedGauge64 
		MAX-ACCESS read-only 
		STATUS current
		DESCRIPTION  "Current Data Proxy" 
		::={ acosSlbImapProxyS 27 } 

		dataTotal OBJECT-TYPE
		SYNTAX  CounterBasedGauge64 
		MAX-ACCESS read-only 
		STATUS current
		DESCRIPTION  "Total Data Proxy" 
		::={ acosSlbImapProxyS 28 } 

		authUnsupported OBJECT-TYPE
		SYNTAX  CounterBasedGauge64 
		MAX-ACCESS read-only 
		STATUS current
		DESCRIPTION  "Unsupported auth" 
		::={ acosSlbImapProxyS 29 } 

		adat OBJECT-TYPE
		SYNTAX  CounterBasedGauge64 
		MAX-ACCESS read-only 
		STATUS current
		DESCRIPTION  "adat cmd" 
		::={ acosSlbImapProxyS 30 } 

		unsupportedPbszValue OBJECT-TYPE
		SYNTAX  CounterBasedGauge64 
		MAX-ACCESS read-only 
		STATUS current
		DESCRIPTION  "Unsupported PBSZ" 
		::={ acosSlbImapProxyS 31 } 

		unsupportedProtValue OBJECT-TYPE
		SYNTAX  CounterBasedGauge64 
		MAX-ACCESS read-only 
		STATUS current
		DESCRIPTION  "Unsupported PROT" 
		::={ acosSlbImapProxyS 32 } 

		unsupportedCommand OBJECT-TYPE
		SYNTAX  CounterBasedGauge64 
		MAX-ACCESS read-only 
		STATUS current
		DESCRIPTION  "Unsupported cmd" 
		::={ acosSlbImapProxyS 33 } 

		controlToClear OBJECT-TYPE
		SYNTAX  CounterBasedGauge64 
		MAX-ACCESS read-only 
		STATUS current
		DESCRIPTION  "Control chn clear txt" 
		::={ acosSlbImapProxyS 34 } 

		controlToSsl OBJECT-TYPE
		SYNTAX  CounterBasedGauge64 
		MAX-ACCESS read-only 
		STATUS current
		DESCRIPTION  "Control chn ssl" 
		::={ acosSlbImapProxyS 35 } 

		badSequence OBJECT-TYPE
		SYNTAX  CounterBasedGauge64 
		MAX-ACCESS read-only 
		STATUS current
		DESCRIPTION  "Bad Sequence" 
		::={ acosSlbImapProxyS 36 } 

		rsvPersistConnFail OBJECT-TYPE
		SYNTAX  CounterBasedGauge64 
		MAX-ACCESS read-only 
		STATUS current
		DESCRIPTION  "Serv Sel Persist fail" 
		::={ acosSlbImapProxyS 37 } 

		smpV6Fail OBJECT-TYPE
		SYNTAX  CounterBasedGauge64 
		MAX-ACCESS read-only 
		STATUS current
		DESCRIPTION  "Serv Sel SMPv6 fail" 
		::={ acosSlbImapProxyS 38 } 

		smpV4Fail OBJECT-TYPE
		SYNTAX  CounterBasedGauge64 
		MAX-ACCESS read-only 
		STATUS current
		DESCRIPTION  "Serv Sel SMPv4 fail" 
		::={ acosSlbImapProxyS 39 } 

		insertTupleFail OBJECT-TYPE
		SYNTAX  CounterBasedGauge64 
		MAX-ACCESS read-only 
		STATUS current
		DESCRIPTION  "Serv Sel insert tuple fail" 
		::={ acosSlbImapProxyS 40 } 

		clEstErr OBJECT-TYPE
		SYNTAX  CounterBasedGauge64 
		MAX-ACCESS read-only 
		STATUS current
		DESCRIPTION  "Client EST state erro" 
		::={ acosSlbImapProxyS 41 } 

		serConnectingErr OBJECT-TYPE
		SYNTAX  CounterBasedGauge64 
		MAX-ACCESS read-only 
		STATUS current
		DESCRIPTION  "Serv CTNG state error" 
		::={ acosSlbImapProxyS 42 } 

		serverResponseErr OBJECT-TYPE
		SYNTAX  CounterBasedGauge64 
		MAX-ACCESS read-only 
		STATUS current
		DESCRIPTION  "Serv RESP state error" 
		::={ acosSlbImapProxyS 43 } 

		clRequestErr OBJECT-TYPE
		SYNTAX  CounterBasedGauge64 
		MAX-ACCESS read-only 
		STATUS current
		DESCRIPTION  "Client RQ state error" 
		::={ acosSlbImapProxyS 44 } 

		dataConnStartErr OBJECT-TYPE
		SYNTAX  CounterBasedGauge64 
		MAX-ACCESS read-only 
		STATUS current
		DESCRIPTION  "Data Start state error" 
		::={ acosSlbImapProxyS 45 } 

		dataServConnectingErr OBJECT-TYPE
		SYNTAX  CounterBasedGauge64 
		MAX-ACCESS read-only 
		STATUS current
		DESCRIPTION  "Data Serv CTNG error" 
		::={ acosSlbImapProxyS 46 } 

		dataServConnectedErr OBJECT-TYPE
		SYNTAX  CounterBasedGauge64 
		MAX-ACCESS read-only 
		STATUS current
		DESCRIPTION  "Data Serv CTED error" 
		::={ acosSlbImapProxyS 47 } 

		request OBJECT-TYPE
		SYNTAX  CounterBasedGauge64 
		MAX-ACCESS read-only 
		STATUS current
		DESCRIPTION  "Total FTP Request" 
		::={ acosSlbImapProxyS 48 } 

		capability OBJECT-TYPE
		SYNTAX  CounterBasedGauge64 
		MAX-ACCESS read-only 
		STATUS current
		DESCRIPTION  "Capability cmd" 
		::={ acosSlbImapProxyS 49 } 

		startTls OBJECT-TYPE
		SYNTAX  CounterBasedGauge64 
		MAX-ACCESS read-only 
		STATUS current
		DESCRIPTION  "Total Start TLS cmd" 
		::={ acosSlbImapProxyS 50 } 

		login OBJECT-TYPE
		SYNTAX  CounterBasedGauge64 
		MAX-ACCESS read-only 
		STATUS current
		DESCRIPTION  "Total Login cmd" 
		::={ acosSlbImapProxyS 51 } 

		reallocError OBJECT-TYPE
		SYNTAX  CounterBasedGauge64 
		MAX-ACCESS read-only 
		STATUS current
		DESCRIPTION  "Realloc error" 
		::={ acosSlbImapProxyS 52 } 

		allocError OBJECT-TYPE
		SYNTAX  CounterBasedGauge64 
		MAX-ACCESS read-only 
		STATUS current
		DESCRIPTION  "Alloc error" 
		::={ acosSlbImapProxyS 53 } 

		boundaryError OBJECT-TYPE
		SYNTAX  CounterBasedGauge64 
		MAX-ACCESS read-only 
		STATUS current
		DESCRIPTION  "Boundary error" 
		::={ acosSlbImapProxyS 54 } 

		negativeError OBJECT-TYPE
		SYNTAX  CounterBasedGauge64 
		MAX-ACCESS read-only 
		STATUS current
		DESCRIPTION  "Negative error" 
		::={ acosSlbImapProxyS 55 } 

acosSlbPop3Proxy                    OBJECT IDENTIFIER ::= { acosSlb 52 }
acosSlbPop3ProxyS                   OBJECT IDENTIFIER ::= { acosSlbPop3Proxy 1 }

		num OBJECT-TYPE
		SYNTAX  CounterBasedGauge64 
		MAX-ACCESS read-only 
		STATUS current
		DESCRIPTION  "Num" 
		::={ acosSlbPop3ProxyS 1 } 

		curr OBJECT-TYPE
		SYNTAX  CounterBasedGauge64 
		MAX-ACCESS read-only 
		STATUS current
		DESCRIPTION  "Current proxy conns" 
		::={ acosSlbPop3ProxyS 2 } 

		total OBJECT-TYPE
		SYNTAX  CounterBasedGauge64 
		MAX-ACCESS read-only 
		STATUS current
		DESCRIPTION  "Total proxy conns" 
		::={ acosSlbPop3ProxyS 3 } 

		svrselFail OBJECT-TYPE
		SYNTAX  CounterBasedGauge64 
		MAX-ACCESS read-only 
		STATUS current
		DESCRIPTION  "Server selection failure" 
		::={ acosSlbPop3ProxyS 4 } 

		noRoute OBJECT-TYPE
		SYNTAX  CounterBasedGauge64 
		MAX-ACCESS read-only 
		STATUS current
		DESCRIPTION  "no route failure" 
		::={ acosSlbPop3ProxyS 5 } 

		snatFail OBJECT-TYPE
		SYNTAX  CounterBasedGauge64 
		MAX-ACCESS read-only 
		STATUS current
		DESCRIPTION  "source nat failure" 
		::={ acosSlbPop3ProxyS 6 } 

		lineTooLong OBJECT-TYPE
		SYNTAX  CounterBasedGauge64 
		MAX-ACCESS read-only 
		STATUS current
		DESCRIPTION  "line too long" 
		::={ acosSlbPop3ProxyS 7 } 

		lineMemFreed OBJECT-TYPE
		SYNTAX  CounterBasedGauge64 
		MAX-ACCESS read-only 
		STATUS current
		DESCRIPTION  "request line freed" 
		::={ acosSlbPop3ProxyS 8 } 

		invalidStartLine OBJECT-TYPE
		SYNTAX  CounterBasedGauge64 
		MAX-ACCESS read-only 
		STATUS current
		DESCRIPTION  "invalid start line" 
		::={ acosSlbPop3ProxyS 9 } 

		stls OBJECT-TYPE
		SYNTAX  CounterBasedGauge64 
		MAX-ACCESS read-only 
		STATUS current
		DESCRIPTION  "stls cmd" 
		::={ acosSlbPop3ProxyS 10 } 

		requestDontCare OBJECT-TYPE
		SYNTAX  CounterBasedGauge64 
		MAX-ACCESS read-only 
		STATUS current
		DESCRIPTION  "other cmd" 
		::={ acosSlbPop3ProxyS 11 } 

		unsupportedCommand OBJECT-TYPE
		SYNTAX  CounterBasedGauge64 
		MAX-ACCESS read-only 
		STATUS current
		DESCRIPTION  "Unsupported cmd" 
		::={ acosSlbPop3ProxyS 12 } 

		badSequence OBJECT-TYPE
		SYNTAX  CounterBasedGauge64 
		MAX-ACCESS read-only 
		STATUS current
		DESCRIPTION  "Bad Sequence" 
		::={ acosSlbPop3ProxyS 13 } 

		rsvPersistConnFail OBJECT-TYPE
		SYNTAX  CounterBasedGauge64 
		MAX-ACCESS read-only 
		STATUS current
		DESCRIPTION  "Serv Sel Persist fail" 
		::={ acosSlbPop3ProxyS 14 } 

		smpV6Fail OBJECT-TYPE
		SYNTAX  CounterBasedGauge64 
		MAX-ACCESS read-only 
		STATUS current
		DESCRIPTION  "Serv Sel SMPv6 fail" 
		::={ acosSlbPop3ProxyS 15 } 

		smpV4Fail OBJECT-TYPE
		SYNTAX  CounterBasedGauge64 
		MAX-ACCESS read-only 
		STATUS current
		DESCRIPTION  "Serv Sel SMPv4 fail" 
		::={ acosSlbPop3ProxyS 16 } 

		insertTupleFail OBJECT-TYPE
		SYNTAX  CounterBasedGauge64 
		MAX-ACCESS read-only 
		STATUS current
		DESCRIPTION  "Serv Sel insert tuple fail" 
		::={ acosSlbPop3ProxyS 17 } 

		clEstErr OBJECT-TYPE
		SYNTAX  CounterBasedGauge64 
		MAX-ACCESS read-only 
		STATUS current
		DESCRIPTION  "Client EST state erro" 
		::={ acosSlbPop3ProxyS 18 } 

		serConnectingErr OBJECT-TYPE
		SYNTAX  CounterBasedGauge64 
		MAX-ACCESS read-only 
		STATUS current
		DESCRIPTION  "Serv CTNG state error" 
		::={ acosSlbPop3ProxyS 19 } 

		serverResponseErr OBJECT-TYPE
		SYNTAX  CounterBasedGauge64 
		MAX-ACCESS read-only 
		STATUS current
		DESCRIPTION  "Serv RESP state error" 
		::={ acosSlbPop3ProxyS 20 } 

		clRequestErr OBJECT-TYPE
		SYNTAX  CounterBasedGauge64 
		MAX-ACCESS read-only 
		STATUS current
		DESCRIPTION  "Client RQ state error" 
		::={ acosSlbPop3ProxyS 21 } 

		request OBJECT-TYPE
		SYNTAX  CounterBasedGauge64 
		MAX-ACCESS read-only 
		STATUS current
		DESCRIPTION  "Total POP3 Request" 
		::={ acosSlbPop3ProxyS 22 } 

		controlToSsl OBJECT-TYPE
		SYNTAX  CounterBasedGauge64 
		MAX-ACCESS read-only 
		STATUS current
		DESCRIPTION  "Control chn ssl" 
		::={ acosSlbPop3ProxyS 23 } 

acosSlbSwitch                       OBJECT IDENTIFIER ::= { acosSlb 53 }
acosSlbSwitchS                      OBJECT IDENTIFIER ::= { acosSlbSwitch 1 }

		fwlb OBJECT-TYPE
		SYNTAX  CounterBasedGauge64 
		MAX-ACCESS read-only 
		STATUS current
		DESCRIPTION  "FWLB" 
		::={ acosSlbSwitchS 1 } 

		licexpireDrop OBJECT-TYPE
		SYNTAX  CounterBasedGauge64 
		MAX-ACCESS read-only 
		STATUS current
		DESCRIPTION  "License Expire Drop" 
		::={ acosSlbSwitchS 2 } 

		bwlDrop OBJECT-TYPE
		SYNTAX  CounterBasedGauge64 
		MAX-ACCESS read-only 
		STATUS current
		DESCRIPTION  "BW Limit Drop" 
		::={ acosSlbSwitchS 3 } 

		rxKernel OBJECT-TYPE
		SYNTAX  CounterBasedGauge64 
		MAX-ACCESS read-only 
		STATUS current
		DESCRIPTION  "Received kernel" 
		::={ acosSlbSwitchS 4 } 

		rxArpReq OBJECT-TYPE
		SYNTAX  CounterBasedGauge64 
		MAX-ACCESS read-only 
		STATUS current
		DESCRIPTION  "ARP REQ Rcvd" 
		::={ acosSlbSwitchS 5 } 

		rxArpResp OBJECT-TYPE
		SYNTAX  CounterBasedGauge64 
		MAX-ACCESS read-only 
		STATUS current
		DESCRIPTION  "ARP RESP Rcvd" 
		::={ acosSlbSwitchS 6 } 

		vlanFlood OBJECT-TYPE
		SYNTAX  CounterBasedGauge64 
		MAX-ACCESS read-only 
		STATUS current
		DESCRIPTION  "VLAN Flood" 
		::={ acosSlbSwitchS 7 } 

		l2DefVlanDrop OBJECT-TYPE
		SYNTAX  CounterBasedGauge64 
		MAX-ACCESS read-only 
		STATUS current
		DESCRIPTION  "L2 Default Vlan FWD Drop" 
		::={ acosSlbSwitchS 8 } 

		ipv4NorouteDrop OBJECT-TYPE
		SYNTAX  CounterBasedGauge64 
		MAX-ACCESS read-only 
		STATUS current
		DESCRIPTION  "IPv4 No Route Drop" 
		::={ acosSlbSwitchS 9 } 

		ipv6NorouteDrop OBJECT-TYPE
		SYNTAX  CounterBasedGauge64 
		MAX-ACCESS read-only 
		STATUS current
		DESCRIPTION  "IPv6 No Route Drop" 
		::={ acosSlbSwitchS 10 } 

		protDownDrop OBJECT-TYPE
		SYNTAX  CounterBasedGauge64 
		MAX-ACCESS read-only 
		STATUS current
		DESCRIPTION  "Prot Down Drop" 
		::={ acosSlbSwitchS 11 } 

		l2Forward OBJECT-TYPE
		SYNTAX  CounterBasedGauge64 
		MAX-ACCESS read-only 
		STATUS current
		DESCRIPTION  "L2 Forward" 
		::={ acosSlbSwitchS 12 } 

		l3ForwardIp OBJECT-TYPE
		SYNTAX  CounterBasedGauge64 
		MAX-ACCESS read-only 
		STATUS current
		DESCRIPTION  "L3 IP Forward" 
		::={ acosSlbSwitchS 13 } 

		l3ForwardIpv6 OBJECT-TYPE
		SYNTAX  CounterBasedGauge64 
		MAX-ACCESS read-only 
		STATUS current
		DESCRIPTION  "L3 IPv6 Forward" 
		::={ acosSlbSwitchS 14 } 

		l4Process OBJECT-TYPE
		SYNTAX  CounterBasedGauge64 
		MAX-ACCESS read-only 
		STATUS current
		DESCRIPTION  "L4 Process" 
		::={ acosSlbSwitchS 15 } 

		unknownProtDrop OBJECT-TYPE
		SYNTAX  CounterBasedGauge64 
		MAX-ACCESS read-only 
		STATUS current
		DESCRIPTION  "Unknown Prot Drop" 
		::={ acosSlbSwitchS 16 } 

		ttlExceededDrop OBJECT-TYPE
		SYNTAX  CounterBasedGauge64 
		MAX-ACCESS read-only 
		STATUS current
		DESCRIPTION  "TTL Exceeded Drop" 
		::={ acosSlbSwitchS 17 } 

		linkdownDrop OBJECT-TYPE
		SYNTAX  CounterBasedGauge64 
		MAX-ACCESS read-only 
		STATUS current
		DESCRIPTION  "Link Down Drop" 
		::={ acosSlbSwitchS 18 } 

		sportDrop OBJECT-TYPE
		SYNTAX  CounterBasedGauge64 
		MAX-ACCESS read-only 
		STATUS current
		DESCRIPTION  "SPORT Drop" 
		::={ acosSlbSwitchS 19 } 

		incorrectLenDrop OBJECT-TYPE
		SYNTAX  CounterBasedGauge64 
		MAX-ACCESS read-only 
		STATUS current
		DESCRIPTION  "Incorrect Length Drop" 
		::={ acosSlbSwitchS 20 } 

		ipDefrag OBJECT-TYPE
		SYNTAX  CounterBasedGauge64 
		MAX-ACCESS read-only 
		STATUS current
		DESCRIPTION  "IP Defrag" 
		::={ acosSlbSwitchS 21 } 

		aclDeny OBJECT-TYPE
		SYNTAX  CounterBasedGauge64 
		MAX-ACCESS read-only 
		STATUS current
		DESCRIPTION  "ACL Denys" 
		::={ acosSlbSwitchS 22 } 

		ipfragTcp OBJECT-TYPE
		SYNTAX  CounterBasedGauge64 
		MAX-ACCESS read-only 
		STATUS current
		DESCRIPTION  "IP(TCP) Fragment Rcvd" 
		::={ acosSlbSwitchS 23 } 

		ipfragOverlap OBJECT-TYPE
		SYNTAX  CounterBasedGauge64 
		MAX-ACCESS read-only 
		STATUS current
		DESCRIPTION  "IP Fragment Overlap" 
		::={ acosSlbSwitchS 24 } 

		ipfragTimeout OBJECT-TYPE
		SYNTAX  CounterBasedGauge64 
		MAX-ACCESS read-only 
		STATUS current
		DESCRIPTION  "IP Fragment Timeout" 
		::={ acosSlbSwitchS 25 } 

		ipfragOverload OBJECT-TYPE
		SYNTAX  CounterBasedGauge64 
		MAX-ACCESS read-only 
		STATUS current
		DESCRIPTION  "IP Frag Overload Drops" 
		::={ acosSlbSwitchS 26 } 

		ipfragReasmoks OBJECT-TYPE
		SYNTAX  CounterBasedGauge64 
		MAX-ACCESS read-only 
		STATUS current
		DESCRIPTION  "IP Fragment Reasm OKs" 
		::={ acosSlbSwitchS 27 } 

		ipfragReasmfails OBJECT-TYPE
		SYNTAX  CounterBasedGauge64 
		MAX-ACCESS read-only 
		STATUS current
		DESCRIPTION  "IP Fragment Reasm Fails" 
		::={ acosSlbSwitchS 28 } 

		landDrop OBJECT-TYPE
		SYNTAX  CounterBasedGauge64 
		MAX-ACCESS read-only 
		STATUS current
		DESCRIPTION  "Anomaly Land Attack Drop" 
		::={ acosSlbSwitchS 29 } 

		ipoptionsDrop OBJECT-TYPE
		SYNTAX  CounterBasedGauge64 
		MAX-ACCESS read-only 
		STATUS current
		DESCRIPTION  "Anomaly IP OPT Drops" 
		::={ acosSlbSwitchS 30 } 

		badpktDrop OBJECT-TYPE
		SYNTAX  CounterBasedGauge64 
		MAX-ACCESS read-only 
		STATUS current
		DESCRIPTION  "Bad Pkt Drop" 
		::={ acosSlbSwitchS 31 } 

		pingofdeathDrop OBJECT-TYPE
		SYNTAX  CounterBasedGauge64 
		MAX-ACCESS read-only 
		STATUS current
		DESCRIPTION  "Anomaly PingDeath Drop" 
		::={ acosSlbSwitchS 32 } 

		allfragDrop OBJECT-TYPE
		SYNTAX  CounterBasedGauge64 
		MAX-ACCESS read-only 
		STATUS current
		DESCRIPTION  "Anomaly All Frag Drop" 
		::={ acosSlbSwitchS 33 } 

		tcpnoflagDrop OBJECT-TYPE
		SYNTAX  CounterBasedGauge64 
		MAX-ACCESS read-only 
		STATUS current
		DESCRIPTION  "Anomaly TCP noFlag Drop" 
		::={ acosSlbSwitchS 34 } 

		tcpsynfragDrop OBJECT-TYPE
		SYNTAX  CounterBasedGauge64 
		MAX-ACCESS read-only 
		STATUS current
		DESCRIPTION  "Anomaly SYN Frag Drop" 
		::={ acosSlbSwitchS 35 } 

		tcpsynfinDrop OBJECT-TYPE
		SYNTAX  CounterBasedGauge64 
		MAX-ACCESS read-only 
		STATUS current
		DESCRIPTION  "Anomaly TCP SYNFIN Drop" 
		::={ acosSlbSwitchS 36 } 

		ipsecDrop OBJECT-TYPE
		SYNTAX  CounterBasedGauge64 
		MAX-ACCESS read-only 
		STATUS current
		DESCRIPTION  "IPSec Drop" 
		::={ acosSlbSwitchS 37 } 

		bpduRcvd OBJECT-TYPE
		SYNTAX  CounterBasedGauge64 
		MAX-ACCESS read-only 
		STATUS current
		DESCRIPTION  "BPDUs Received" 
		::={ acosSlbSwitchS 38 } 

		bpduSent OBJECT-TYPE
		SYNTAX  CounterBasedGauge64 
		MAX-ACCESS read-only 
		STATUS current
		DESCRIPTION  "BPDUs Sent" 
		::={ acosSlbSwitchS 39 } 

		ctrlSynRateDrop OBJECT-TYPE
		SYNTAX  CounterBasedGauge64 
		MAX-ACCESS read-only 
		STATUS current
		DESCRIPTION  "SYN rate exceeded Drop" 
		::={ acosSlbSwitchS 40 } 

		ipDefragInvalidLen OBJECT-TYPE
		SYNTAX  CounterBasedGauge64 
		MAX-ACCESS read-only 
		STATUS current
		DESCRIPTION  "IP Invalid Length Frag" 
		::={ acosSlbSwitchS 41 } 

		ipv4Frag6rdOk OBJECT-TYPE
		SYNTAX  CounterBasedGauge64 
		MAX-ACCESS read-only 
		STATUS current
		DESCRIPTION  "IPv4 Frag 6RD OK" 
		::={ acosSlbSwitchS 42 } 

		ipv4Frag6rdDrop OBJECT-TYPE
		SYNTAX  CounterBasedGauge64 
		MAX-ACCESS read-only 
		STATUS current
		DESCRIPTION  "IPv4 Frag 6RD Dropped" 
		::={ acosSlbSwitchS 43 } 

		noIpDrop OBJECT-TYPE
		SYNTAX  CounterBasedGauge64 
		MAX-ACCESS read-only 
		STATUS current
		DESCRIPTION  "No IP Drop" 
		::={ acosSlbSwitchS 44 } 

		ipv6fragUdp OBJECT-TYPE
		SYNTAX  CounterBasedGauge64 
		MAX-ACCESS read-only 
		STATUS current
		DESCRIPTION  "IPv6 Frag UDP" 
		::={ acosSlbSwitchS 45 } 

		ipv6fragUdpDropped OBJECT-TYPE
		SYNTAX  CounterBasedGauge64 
		MAX-ACCESS read-only 
		STATUS current
		DESCRIPTION  "IPv6 Frag UDP Dropped" 
		::={ acosSlbSwitchS 46 } 

		ipv6fragTcpDropped OBJECT-TYPE
		SYNTAX  CounterBasedGauge64 
		MAX-ACCESS read-only 
		STATUS current
		DESCRIPTION  "IPv6 Frag TCP Dropped" 
		::={ acosSlbSwitchS 47 } 

		ipv6fragIpipOk OBJECT-TYPE
		SYNTAX  CounterBasedGauge64 
		MAX-ACCESS read-only 
		STATUS current
		DESCRIPTION  "IPv6 Frag IPIP OKs" 
		::={ acosSlbSwitchS 48 } 

		ipv6fragIpipDropped OBJECT-TYPE
		SYNTAX  CounterBasedGauge64 
		MAX-ACCESS read-only 
		STATUS current
		DESCRIPTION  "IPv6 Frag IPIP Drop" 
		::={ acosSlbSwitchS 49 } 

		ipFragOversize OBJECT-TYPE
		SYNTAX  CounterBasedGauge64 
		MAX-ACCESS read-only 
		STATUS current
		DESCRIPTION  "IP Fragment oversize" 
		::={ acosSlbSwitchS 50 } 

		ipFragTooMany OBJECT-TYPE
		SYNTAX  CounterBasedGauge64 
		MAX-ACCESS read-only 
		STATUS current
		DESCRIPTION  "IP Fragment too many" 
		::={ acosSlbSwitchS 51 } 

		ipv4NovlanfwdDrop OBJECT-TYPE
		SYNTAX  CounterBasedGauge64 
		MAX-ACCESS read-only 
		STATUS current
		DESCRIPTION  "IPv4 No L3 VLAN FWD Drop" 
		::={ acosSlbSwitchS 52 } 

		ipv6NovlanfwdDrop OBJECT-TYPE
		SYNTAX  CounterBasedGauge64 
		MAX-ACCESS read-only 
		STATUS current
		DESCRIPTION  "IPv6 No L3 VLAN FWD Drop" 
		::={ acosSlbSwitchS 53 } 

		fpgaErrorPkt1 OBJECT-TYPE
		SYNTAX  CounterBasedGauge64 
		MAX-ACCESS read-only 
		STATUS current
		DESCRIPTION  "FPGA Error PKT1" 
		::={ acosSlbSwitchS 54 } 

		fpgaErrorPkt2 OBJECT-TYPE
		SYNTAX  CounterBasedGauge64 
		MAX-ACCESS read-only 
		STATUS current
		DESCRIPTION  "FPGA Error PKT2" 
		::={ acosSlbSwitchS 55 } 

		maxArpDrop OBJECT-TYPE
		SYNTAX  CounterBasedGauge64 
		MAX-ACCESS read-only 
		STATUS current
		DESCRIPTION  "Max ARP Drop" 
		::={ acosSlbSwitchS 56 } 

		ipv6fragTcp OBJECT-TYPE
		SYNTAX  CounterBasedGauge64 
		MAX-ACCESS read-only 
		STATUS current
		DESCRIPTION  "IPv6 Frag TCP" 
		::={ acosSlbSwitchS 57 } 

		ipv6fragIcmp OBJECT-TYPE
		SYNTAX  CounterBasedGauge64 
		MAX-ACCESS read-only 
		STATUS current
		DESCRIPTION  "IPv6 Frag ICMP" 
		::={ acosSlbSwitchS 58 } 

		ipv6fragOspf OBJECT-TYPE
		SYNTAX  CounterBasedGauge64 
		MAX-ACCESS read-only 
		STATUS current
		DESCRIPTION  "IPv6 Frag OSPF" 
		::={ acosSlbSwitchS 59 } 

		ipv6fragEsp OBJECT-TYPE
		SYNTAX  CounterBasedGauge64 
		MAX-ACCESS read-only 
		STATUS current
		DESCRIPTION  "IPv6 Frag ESP" 
		::={ acosSlbSwitchS 60 } 

		l4InCtrlCpu OBJECT-TYPE
		SYNTAX  CounterBasedGauge64 
		MAX-ACCESS read-only 
		STATUS current
		DESCRIPTION  "L4 In Ctrl CPU" 
		::={ acosSlbSwitchS 61 } 

		mgmtSvcDrop OBJECT-TYPE
		SYNTAX  CounterBasedGauge64 
		MAX-ACCESS read-only 
		STATUS current
		DESCRIPTION  "Management Service Drop" 
		::={ acosSlbSwitchS 62 } 

		jumboFragDrop OBJECT-TYPE
		SYNTAX  CounterBasedGauge64 
		MAX-ACCESS read-only 
		STATUS current
		DESCRIPTION  "Jumbo Frag Drop" 
		::={ acosSlbSwitchS 63 } 

		ipv6JumboFragDrop OBJECT-TYPE
		SYNTAX  CounterBasedGauge64 
		MAX-ACCESS read-only 
		STATUS current
		DESCRIPTION  "IPv6 Jumbo Frag Drop" 
		::={ acosSlbSwitchS 64 } 

		ipipv6JumboFragDrop OBJECT-TYPE
		SYNTAX  CounterBasedGauge64 
		MAX-ACCESS read-only 
		STATUS current
		DESCRIPTION  "IPIPv6 Jumbo Frag Drop" 
		::={ acosSlbSwitchS 65 } 

		ipv6NdiscDadSolicits OBJECT-TYPE
		SYNTAX  CounterBasedGauge64 
		MAX-ACCESS read-only 
		STATUS current
		DESCRIPTION  "IPv6 DAD on Solicits" 
		::={ acosSlbSwitchS 66 } 

		ipv6NdiscDadAdverts OBJECT-TYPE
		SYNTAX  CounterBasedGauge64 
		MAX-ACCESS read-only 
		STATUS current
		DESCRIPTION  "IPv6 DAD on Adverts" 
		::={ acosSlbSwitchS 67 } 

		ipv6NdiscMacChanges OBJECT-TYPE
		SYNTAX  CounterBasedGauge64 
		MAX-ACCESS read-only 
		STATUS current
		DESCRIPTION  "IPv6 DAD MAC Changed" 
		::={ acosSlbSwitchS 68 } 

		ipv6NdiscOutOfMemory OBJECT-TYPE
		SYNTAX  CounterBasedGauge64 
		MAX-ACCESS read-only 
		STATUS current
		DESCRIPTION  "IPv6 DAD Out-of-memory" 
		::={ acosSlbSwitchS 69 } 

		spNonCtrlPktDrop OBJECT-TYPE
		SYNTAX  CounterBasedGauge64 
		MAX-ACCESS read-only 
		STATUS current
		DESCRIPTION  "Shared IP mode non ctrl packet to linux drop" 
		::={ acosSlbSwitchS 70 } 

		urpfPktDrop OBJECT-TYPE
		SYNTAX  CounterBasedGauge64 
		MAX-ACCESS read-only 
		STATUS current
		DESCRIPTION  "URPF check packet drop" 
		::={ acosSlbSwitchS 71 } 

		fwSmpZoneMismatch OBJECT-TYPE
		SYNTAX  CounterBasedGauge64 
		MAX-ACCESS read-only 
		STATUS current
		DESCRIPTION  "FW SMP Zone Mismatch" 
		::={ acosSlbSwitchS 72 } 

		ipfragUdp OBJECT-TYPE
		SYNTAX  CounterBasedGauge64 
		MAX-ACCESS read-only 
		STATUS current
		DESCRIPTION  "IP(UDP) Fragment Rcvd" 
		::={ acosSlbSwitchS 73 } 

		ipfragIcmp OBJECT-TYPE
		SYNTAX  CounterBasedGauge64 
		MAX-ACCESS read-only 
		STATUS current
		DESCRIPTION  "IP(ICMP) Fragment Rcvd" 
		::={ acosSlbSwitchS 74 } 

		ipfragOspf OBJECT-TYPE
		SYNTAX  CounterBasedGauge64 
		MAX-ACCESS read-only 
		STATUS current
		DESCRIPTION  "IP(OSPF) Fragment Rcvd" 
		::={ acosSlbSwitchS 75 } 

		ipfragEsp OBJECT-TYPE
		SYNTAX  CounterBasedGauge64 
		MAX-ACCESS read-only 
		STATUS current
		DESCRIPTION  "IP(ESP) Fragment Rcvd" 
		::={ acosSlbSwitchS 76 } 

		ipfragTcpDropped OBJECT-TYPE
		SYNTAX  CounterBasedGauge64 
		MAX-ACCESS read-only 
		STATUS current
		DESCRIPTION  "IP Frag TCP Dropped" 
		::={ acosSlbSwitchS 77 } 

		ipfragUdpDropped OBJECT-TYPE
		SYNTAX  CounterBasedGauge64 
		MAX-ACCESS read-only 
		STATUS current
		DESCRIPTION  "IP Frag UDP Dropped" 
		::={ acosSlbSwitchS 78 } 

		ipfragIpipDropped OBJECT-TYPE
		SYNTAX  CounterBasedGauge64 
		MAX-ACCESS read-only 
		STATUS current
		DESCRIPTION  "IP Frag IPIP Drop" 
		::={ acosSlbSwitchS 79 } 

		redirectFwdFail OBJECT-TYPE
		SYNTAX  CounterBasedGauge64 
		MAX-ACCESS read-only 
		STATUS current
		DESCRIPTION  "Redirect failed in the fwd direction" 
		::={ acosSlbSwitchS 80 } 

		redirectFwdSent OBJECT-TYPE
		SYNTAX  CounterBasedGauge64 
		MAX-ACCESS read-only 
		STATUS current
		DESCRIPTION  "Redirect succeeded in the fwd direction" 
		::={ acosSlbSwitchS 81 } 

		redirectRevFail OBJECT-TYPE
		SYNTAX  CounterBasedGauge64 
		MAX-ACCESS read-only 
		STATUS current
		DESCRIPTION  "Redirect failed in the rev direction" 
		::={ acosSlbSwitchS 82 } 

		redirectRevSent OBJECT-TYPE
		SYNTAX  CounterBasedGauge64 
		MAX-ACCESS read-only 
		STATUS current
		DESCRIPTION  "Redirect succeeded in the rev direction" 
		::={ acosSlbSwitchS 83 } 

		redirectSetupFail OBJECT-TYPE
		SYNTAX  CounterBasedGauge64 
		MAX-ACCESS read-only 
		STATUS current
		DESCRIPTION  "Redirect connection setup failed" 
		::={ acosSlbSwitchS 84 } 

		ipFragSent OBJECT-TYPE
		SYNTAX  CounterBasedGauge64 
		MAX-ACCESS read-only 
		STATUS current
		DESCRIPTION  "IP frag sent" 
		::={ acosSlbSwitchS 85 } 

		invalidRxArpPkt OBJECT-TYPE
		SYNTAX  CounterBasedGauge64 
		MAX-ACCESS read-only 
		STATUS current
		DESCRIPTION  "Invalid ARP PKT Rcvd" 
		::={ acosSlbSwitchS 86 } 

		invalidSenderMacArpDrop OBJECT-TYPE
		SYNTAX  CounterBasedGauge64 
		MAX-ACCESS read-only 
		STATUS current
		DESCRIPTION  "ARP PKT dropped due to invalid sender MAC" 
		::={ acosSlbSwitchS 87 } 

		devBasedArpDrop OBJECT-TYPE
		SYNTAX  CounterBasedGauge64 
		MAX-ACCESS read-only 
		STATUS current
		DESCRIPTION  "ARP PKT dropped due to interface state checks" 
		::={ acosSlbSwitchS 88 } 

		scaleoutArpDrop OBJECT-TYPE
		SYNTAX  CounterBasedGauge64 
		MAX-ACCESS read-only 
		STATUS current
		DESCRIPTION  "ARP PKT dropped due to scaleout checks" 
		::={ acosSlbSwitchS 89 } 

		virtualIpNotFoundArpDrop OBJECT-TYPE
		SYNTAX  CounterBasedGauge64 
		MAX-ACCESS read-only 
		STATUS current
		DESCRIPTION  "ARP PKT dropped due to virtual IP not found" 
		::={ acosSlbSwitchS 90 } 

		inactiveStaticNatPoolArpDrop OBJECT-TYPE
		SYNTAX  CounterBasedGauge64 
		MAX-ACCESS read-only 
		STATUS current
		DESCRIPTION  "ARP PKT dropped due to inactive static nat pool" 
		::={ acosSlbSwitchS 91 } 

		inactiveNatPoolArpDrop OBJECT-TYPE
		SYNTAX  CounterBasedGauge64 
		MAX-ACCESS read-only 
		STATUS current
		DESCRIPTION  "ARP PKT dropped due to inactive nat pool" 
		::={ acosSlbSwitchS 92 } 

		scaleoutHairpinArpDrop OBJECT-TYPE
		SYNTAX  CounterBasedGauge64 
		MAX-ACCESS read-only 
		STATUS current
		DESCRIPTION  "ARP PKT dropped due to scaleout hairpin checks" 
		::={ acosSlbSwitchS 93 } 

		selfGratArpDrop OBJECT-TYPE
		SYNTAX  CounterBasedGauge64 
		MAX-ACCESS read-only 
		STATUS current
		DESCRIPTION  "Self generated grat ARP PKT dropped" 
		::={ acosSlbSwitchS 94 } 

		selfGratNatIpArpDrop OBJECT-TYPE
		SYNTAX  CounterBasedGauge64 
		MAX-ACCESS read-only 
		STATUS current
		DESCRIPTION  "Self generated grat ARP PKT dropped for NAT IP" 
		::={ acosSlbSwitchS 95 } 

		ipNotFoundArpDrop OBJECT-TYPE
		SYNTAX  CounterBasedGauge64 
		MAX-ACCESS read-only 
		STATUS current
		DESCRIPTION  "ARP PKT dropped due to IP not found" 
		::={ acosSlbSwitchS 96 } 

		devLinkDownArpDrop OBJECT-TYPE
		SYNTAX  CounterBasedGauge64 
		MAX-ACCESS read-only 
		STATUS current
		DESCRIPTION  "ARP PKT dropped due to interface is down" 
		::={ acosSlbSwitchS 97 } 

		lacpTxIntfErrDrop OBJECT-TYPE
		SYNTAX  CounterBasedGauge64 
		MAX-ACCESS read-only 
		STATUS current
		DESCRIPTION  "LACP interface error corrected" 
		::={ acosSlbSwitchS 98 } 

		serviceChainSent OBJECT-TYPE
		SYNTAX  CounterBasedGauge64 
		MAX-ACCESS read-only 
		STATUS current
		DESCRIPTION  "Service Chain Packets Sent" 
		::={ acosSlbSwitchS 99 } 

		serviceChainRcvd OBJECT-TYPE
		SYNTAX  CounterBasedGauge64 
		MAX-ACCESS read-only 
		STATUS current
		DESCRIPTION  "Service Chain Packets Rcvd" 
		::={ acosSlbSwitchS 100 } 

		unnumberedNatError OBJECT-TYPE
		SYNTAX  CounterBasedGauge64 
		MAX-ACCESS read-only 
		STATUS current
		DESCRIPTION  "Unnumbered NAT error" 
		::={ acosSlbSwitchS 101 } 

		unnumberedUnsupportedDrop OBJECT-TYPE
		SYNTAX  CounterBasedGauge64 
		MAX-ACCESS read-only 
		STATUS current
		DESCRIPTION  "Unsupported protocol for unnumbered" 
		::={ acosSlbSwitchS 102 } 

		ipv6fragGreDropped OBJECT-TYPE
		SYNTAX  CounterBasedGauge64 
		MAX-ACCESS read-only 
		STATUS current
		DESCRIPTION  "IPv6 Frag gre Drop" 
		::={ acosSlbSwitchS 103 } 

		ipv6NdiscDadPrefixMismatchDrop OBJECT-TYPE
		SYNTAX  CounterBasedGauge64 
		MAX-ACCESS read-only 
		STATUS current
		DESCRIPTION  "IPv6 DAD on Advertise drop for prefix mismatch" 
		::={ acosSlbSwitchS 104 } 

		bwIgnoreLimit OBJECT-TYPE
		SYNTAX  CounterBasedGauge64 
		MAX-ACCESS read-only 
		STATUS current
		DESCRIPTION  "BW Limit ignored packets count" 
		::={ acosSlbSwitchS 105 } 

		ppslDropEgr OBJECT-TYPE
		SYNTAX  CounterBasedGauge64 
		MAX-ACCESS read-only 
		STATUS current
		DESCRIPTION  "Packet-Per-Sec Limit Drop at egress" 
		::={ acosSlbSwitchS 106 } 

		ppslDropIng OBJECT-TYPE
		SYNTAX  CounterBasedGauge64 
		MAX-ACCESS read-only 
		STATUS current
		DESCRIPTION  "Packet-Per-Sec Limit Drop at ingress" 
		::={ acosSlbSwitchS 107 } 

		ppslIgnoreLimit OBJECT-TYPE
		SYNTAX  CounterBasedGauge64 
		MAX-ACCESS read-only 
		STATUS current
		DESCRIPTION  "Packet-Per-Sec Limit ignored packets count" 
		::={ acosSlbSwitchS 108 } 

		closedPortSynDrop OBJECT-TYPE
		SYNTAX  CounterBasedGauge64 
		MAX-ACCESS read-only 
		STATUS current
		DESCRIPTION  "Linux Closed Port SYN Drop" 
		::={ acosSlbSwitchS 109 } 

		ipIcmpErrorDrop OBJECT-TYPE
		SYNTAX  CounterBasedGauge64 
		MAX-ACCESS read-only 
		STATUS current
		DESCRIPTION  "IP ICMP Error Drop" 
		::={ acosSlbSwitchS 110 } 

		tls13DropReq OBJECT-TYPE
		SYNTAX  CounterBasedGauge64 
		MAX-ACCESS read-only 
		STATUS current
		DESCRIPTION  "TLS13-Request-Per-Sec Limit Drop at ingress" 
		::={ acosSlbSwitchS 111 } 

		tls13IgnoreReq OBJECT-TYPE
		SYNTAX  CounterBasedGauge64 
		MAX-ACCESS read-only 
		STATUS current
		DESCRIPTION  "TLS13-Request-Per-Sec Limit ignored packets count" 
		::={ acosSlbSwitchS 112 } 

		tls12DropReq OBJECT-TYPE
		SYNTAX  CounterBasedGauge64 
		MAX-ACCESS read-only 
		STATUS current
		DESCRIPTION  "TLS12-Request-Per-Sec Limit Drop at ingress" 
		::={ acosSlbSwitchS 113 } 

		tls12IgnoreReq OBJECT-TYPE
		SYNTAX  CounterBasedGauge64 
		MAX-ACCESS read-only 
		STATUS current
		DESCRIPTION  "TLS12-Request-Per-Sec Limit ignored packets count" 
		::={ acosSlbSwitchS 114 } 

		tls12Tls13DropReq OBJECT-TYPE
		SYNTAX  CounterBasedGauge64 
		MAX-ACCESS read-only 
		STATUS current
		DESCRIPTION  "TLS12--TLS13-Request-Per-Sec Limit Drop at ingress" 
		::={ acosSlbSwitchS 115 } 

		tls12Tls13IgnoreReq OBJECT-TYPE
		SYNTAX  CounterBasedGauge64 
		MAX-ACCESS read-only 
		STATUS current
		DESCRIPTION  "TLS12-TLS13-Request-Per-Sec Limit ignored packets count" 
		::={ acosSlbSwitchS 116 } 

acosSlbProxy                        OBJECT IDENTIFIER ::= { acosSlb 54 }
acosSlbProxyS                       OBJECT IDENTIFIER ::= { acosSlbProxy 1 }

		num OBJECT-TYPE
		SYNTAX  CounterBasedGauge64 
		MAX-ACCESS read-only 
		STATUS current
		DESCRIPTION  "Num" 
		::={ acosSlbProxyS 1 } 

		tcpEvent OBJECT-TYPE
		SYNTAX  CounterBasedGauge64 
		MAX-ACCESS read-only 
		STATUS current
		DESCRIPTION  "TCP stack event" 
		::={ acosSlbProxyS 2 } 

		estEvent OBJECT-TYPE
		SYNTAX  CounterBasedGauge64 
		MAX-ACCESS read-only 
		STATUS current
		DESCRIPTION  "Connection established" 
		::={ acosSlbProxyS 3 } 

		dataEvent OBJECT-TYPE
		SYNTAX  CounterBasedGauge64 
		MAX-ACCESS read-only 
		STATUS current
		DESCRIPTION  "Data received" 
		::={ acosSlbProxyS 4 } 

		slbProxyClientFin OBJECT-TYPE
		SYNTAX  CounterBasedGauge64 
		MAX-ACCESS read-only 
		STATUS current
		DESCRIPTION  "Client FIN" 
		::={ acosSlbProxyS 5 } 

		slbProxyServerFin OBJECT-TYPE
		SYNTAX  CounterBasedGauge64 
		MAX-ACCESS read-only 
		STATUS current
		DESCRIPTION  "Server FIN" 
		::={ acosSlbProxyS 6 } 

		wbufEvent OBJECT-TYPE
		SYNTAX  CounterBasedGauge64 
		MAX-ACCESS read-only 
		STATUS current
		DESCRIPTION  "Ready to send data" 
		::={ acosSlbProxyS 7 } 

		errEvent OBJECT-TYPE
		SYNTAX  CounterBasedGauge64 
		MAX-ACCESS read-only 
		STATUS current
		DESCRIPTION  "Error occured" 
		::={ acosSlbProxyS 8 } 

		noMem OBJECT-TYPE
		SYNTAX  CounterBasedGauge64 
		MAX-ACCESS read-only 
		STATUS current
		DESCRIPTION  "No memory" 
		::={ acosSlbProxyS 9 } 

		slbProxyClientRst OBJECT-TYPE
		SYNTAX  CounterBasedGauge64 
		MAX-ACCESS read-only 
		STATUS current
		DESCRIPTION  "Client RST" 
		::={ acosSlbProxyS 10 } 

		slbProxyServerRst OBJECT-TYPE
		SYNTAX  CounterBasedGauge64 
		MAX-ACCESS read-only 
		STATUS current
		DESCRIPTION  "Server RST" 
		::={ acosSlbProxyS 11 } 

		queueDepthOverLimit OBJECT-TYPE
		SYNTAX  CounterBasedGauge64 
		MAX-ACCESS read-only 
		STATUS current
		DESCRIPTION  "Queue depth over limit" 
		::={ acosSlbProxyS 12 } 

		eventFailed OBJECT-TYPE
		SYNTAX  CounterBasedGauge64 
		MAX-ACCESS read-only 
		STATUS current
		DESCRIPTION  "Event failed" 
		::={ acosSlbProxyS 13 } 

		connNotExist OBJECT-TYPE
		SYNTAX  CounterBasedGauge64 
		MAX-ACCESS read-only 
		STATUS current
		DESCRIPTION  "Conn not exist" 
		::={ acosSlbProxyS 14 } 

		serviceAllocCb OBJECT-TYPE
		SYNTAX  CounterBasedGauge64 
		MAX-ACCESS read-only 
		STATUS current
		DESCRIPTION  "Service alloc callback" 
		::={ acosSlbProxyS 15 } 

		serviceAllocCbFailed OBJECT-TYPE
		SYNTAX  CounterBasedGauge64 
		MAX-ACCESS read-only 
		STATUS current
		DESCRIPTION  "Service alloc callback failed" 
		::={ acosSlbProxyS 16 } 

		serviceFreeCb OBJECT-TYPE
		SYNTAX  CounterBasedGauge64 
		MAX-ACCESS read-only 
		STATUS current
		DESCRIPTION  "Service free callback" 
		::={ acosSlbProxyS 17 } 

		serviceFreeCbFailed OBJECT-TYPE
		SYNTAX  CounterBasedGauge64 
		MAX-ACCESS read-only 
		STATUS current
		DESCRIPTION  "Service free callback failed" 
		::={ acosSlbProxyS 18 } 

		estCbFailed OBJECT-TYPE
		SYNTAX  CounterBasedGauge64 
		MAX-ACCESS read-only 
		STATUS current
		DESCRIPTION  "App EST callback failed" 
		::={ acosSlbProxyS 19 } 

		dataCbFailed OBJECT-TYPE
		SYNTAX  CounterBasedGauge64 
		MAX-ACCESS read-only 
		STATUS current
		DESCRIPTION  "App DATA callback failed" 
		::={ acosSlbProxyS 20 } 

		wbufCbFailed OBJECT-TYPE
		SYNTAX  CounterBasedGauge64 
		MAX-ACCESS read-only 
		STATUS current
		DESCRIPTION  "App WBUF callback failed" 
		::={ acosSlbProxyS 21 } 

		errCbFailed OBJECT-TYPE
		SYNTAX  CounterBasedGauge64 
		MAX-ACCESS read-only 
		STATUS current
		DESCRIPTION  "App ERR callback failed" 
		::={ acosSlbProxyS 22 } 

		startServerConn OBJECT-TYPE
		SYNTAX  CounterBasedGauge64 
		MAX-ACCESS read-only 
		STATUS current
		DESCRIPTION  "Start server conn" 
		::={ acosSlbProxyS 23 } 

		startServerConnSucc OBJECT-TYPE
		SYNTAX  CounterBasedGauge64 
		MAX-ACCESS read-only 
		STATUS current
		DESCRIPTION  "Success" 
		::={ acosSlbProxyS 24 } 

		startServerConnNoRoute OBJECT-TYPE
		SYNTAX  CounterBasedGauge64 
		MAX-ACCESS read-only 
		STATUS current
		DESCRIPTION  "No route to server" 
		::={ acosSlbProxyS 25 } 

		startServerConnFailMem OBJECT-TYPE
		SYNTAX  CounterBasedGauge64 
		MAX-ACCESS read-only 
		STATUS current
		DESCRIPTION  "No memory" 
		::={ acosSlbProxyS 26 } 

		startServerConnFailSnat OBJECT-TYPE
		SYNTAX  CounterBasedGauge64 
		MAX-ACCESS read-only 
		STATUS current
		DESCRIPTION  "Failed Source NAT" 
		::={ acosSlbProxyS 27 } 

		startServerConnFailPersist OBJECT-TYPE
		SYNTAX  CounterBasedGauge64 
		MAX-ACCESS read-only 
		STATUS current
		DESCRIPTION  "Fail Persistence" 
		::={ acosSlbProxyS 28 } 

		startServerConnFailServer OBJECT-TYPE
		SYNTAX  CounterBasedGauge64 
		MAX-ACCESS read-only 
		STATUS current
		DESCRIPTION  "Fail Server issue" 
		::={ acosSlbProxyS 29 } 

		startServerConnFailTuple OBJECT-TYPE
		SYNTAX  CounterBasedGauge64 
		MAX-ACCESS read-only 
		STATUS current
		DESCRIPTION  "Fail Tuple Issue" 
		::={ acosSlbProxyS 30 } 

		slbProxyLineTooLong OBJECT-TYPE
		SYNTAX  CounterBasedGauge64 
		MAX-ACCESS read-only 
		STATUS current
		DESCRIPTION  "Line too long" 
		::={ acosSlbProxyS 31 } 

acosSlbRcCacheGlobal                OBJECT IDENTIFIER ::= { acosSlb 55 }
acosSlbRcCacheGlobalS               OBJECT IDENTIFIER ::= { acosSlbRcCacheGlobal 1 }

		rcCacheGlobalHits OBJECT-TYPE
		SYNTAX  CounterBasedGauge64 
		MAX-ACCESS read-only 
		STATUS current
		DESCRIPTION  "Cache Hits" 
		::={ acosSlbRcCacheGlobalS 1 } 

		miss OBJECT-TYPE
		SYNTAX  CounterBasedGauge64 
		MAX-ACCESS read-only 
		STATUS current
		DESCRIPTION  "Cache Misses" 
		::={ acosSlbRcCacheGlobalS 2 } 

		bytesServed OBJECT-TYPE
		SYNTAX  CounterBasedGauge64 
		MAX-ACCESS read-only 
		STATUS current
		DESCRIPTION  "Bytes Served" 
		::={ acosSlbRcCacheGlobalS 3 } 

		rcCacheGlobalTotalReq OBJECT-TYPE
		SYNTAX  CounterBasedGauge64 
		MAX-ACCESS read-only 
		STATUS current
		DESCRIPTION  "Total Requests" 
		::={ acosSlbRcCacheGlobalS 4 } 

		cachingReq OBJECT-TYPE
		SYNTAX  CounterBasedGauge64 
		MAX-ACCESS read-only 
		STATUS current
		DESCRIPTION  "Cacheable Requests" 
		::={ acosSlbRcCacheGlobalS 5 } 

		ncReqHeader OBJECT-TYPE
		SYNTAX  CounterBasedGauge64 
		MAX-ACCESS read-only 
		STATUS current
		DESCRIPTION  "No-cache Request" 
		::={ acosSlbRcCacheGlobalS 6 } 

		ncResHeader OBJECT-TYPE
		SYNTAX  CounterBasedGauge64 
		MAX-ACCESS read-only 
		STATUS current
		DESCRIPTION  "Not cacheable" 
		::={ acosSlbRcCacheGlobalS 7 } 

		rvSuccess OBJECT-TYPE
		SYNTAX  CounterBasedGauge64 
		MAX-ACCESS read-only 
		STATUS current
		DESCRIPTION  "Revalidation Successes" 
		::={ acosSlbRcCacheGlobalS 8 } 

		rvFailure OBJECT-TYPE
		SYNTAX  CounterBasedGauge64 
		MAX-ACCESS read-only 
		STATUS current
		DESCRIPTION  "Revalidation Failures" 
		::={ acosSlbRcCacheGlobalS 9 } 

		imsRequest OBJECT-TYPE
		SYNTAX  CounterBasedGauge64 
		MAX-ACCESS read-only 
		STATUS current
		DESCRIPTION  "IMS Requests" 
		::={ acosSlbRcCacheGlobalS 10 } 

		nmResponse OBJECT-TYPE
		SYNTAX  CounterBasedGauge64 
		MAX-ACCESS read-only 
		STATUS current
		DESCRIPTION  "Responses from cache 304 Not Modified" 
		::={ acosSlbRcCacheGlobalS 11 } 

		rspTypeCL OBJECT-TYPE
		SYNTAX  CounterBasedGauge64 
		MAX-ACCESS read-only 
		STATUS current
		DESCRIPTION  "Responses from server 200 OK - Cont Len" 
		::={ acosSlbRcCacheGlobalS 12 } 

		rspTypeCE OBJECT-TYPE
		SYNTAX  CounterBasedGauge64 
		MAX-ACCESS read-only 
		STATUS current
		DESCRIPTION  "Responses from server 200 OK - Chnk Enc" 
		::={ acosSlbRcCacheGlobalS 13 } 

		rspType304 OBJECT-TYPE
		SYNTAX  CounterBasedGauge64 
		MAX-ACCESS read-only 
		STATUS current
		DESCRIPTION  "Responses from server 304 Not Modified" 
		::={ acosSlbRcCacheGlobalS 14 } 

		rspTypeOther OBJECT-TYPE
		SYNTAX  CounterBasedGauge64 
		MAX-ACCESS read-only 
		STATUS current
		DESCRIPTION  "Responses from server 200 OK - Other" 
		::={ acosSlbRcCacheGlobalS 15 } 

		rspNoCompress OBJECT-TYPE
		SYNTAX  CounterBasedGauge64 
		MAX-ACCESS read-only 
		STATUS current
		DESCRIPTION  "Responses from cache 200 OK - No Comp" 
		::={ acosSlbRcCacheGlobalS 16 } 

		rspGzip OBJECT-TYPE
		SYNTAX  CounterBasedGauge64 
		MAX-ACCESS read-only 
		STATUS current
		DESCRIPTION  "Responses from cache 200 OK - Gzip" 
		::={ acosSlbRcCacheGlobalS 17 } 

		rspDeflate OBJECT-TYPE
		SYNTAX  CounterBasedGauge64 
		MAX-ACCESS read-only 
		STATUS current
		DESCRIPTION  "Responses from cache 200 OK - Deflate" 
		::={ acosSlbRcCacheGlobalS 18 } 

		rspOther OBJECT-TYPE
		SYNTAX  CounterBasedGauge64 
		MAX-ACCESS read-only 
		STATUS current
		DESCRIPTION  "Responses from cache Other" 
		::={ acosSlbRcCacheGlobalS 19 } 

		nocacheMatch OBJECT-TYPE
		SYNTAX  CounterBasedGauge64 
		MAX-ACCESS read-only 
		STATUS current
		DESCRIPTION  "Policy URI nocache" 
		::={ acosSlbRcCacheGlobalS 20 } 

		match OBJECT-TYPE
		SYNTAX  CounterBasedGauge64 
		MAX-ACCESS read-only 
		STATUS current
		DESCRIPTION  "Policy URI cache" 
		::={ acosSlbRcCacheGlobalS 21 } 

		invalidateMatch OBJECT-TYPE
		SYNTAX  CounterBasedGauge64 
		MAX-ACCESS read-only 
		STATUS current
		DESCRIPTION  "Policy URI invalidate" 
		::={ acosSlbRcCacheGlobalS 22 } 

		contentToobig OBJECT-TYPE
		SYNTAX  CounterBasedGauge64 
		MAX-ACCESS read-only 
		STATUS current
		DESCRIPTION  "Policy Content Too Big" 
		::={ acosSlbRcCacheGlobalS 23 } 

		contentToosmall OBJECT-TYPE
		SYNTAX  CounterBasedGauge64 
		MAX-ACCESS read-only 
		STATUS current
		DESCRIPTION  "Policy Content Too Small" 
		::={ acosSlbRcCacheGlobalS 24 } 

		entryCreateFailures OBJECT-TYPE
		SYNTAX  CounterBasedGauge64 
		MAX-ACCESS read-only 
		STATUS current
		DESCRIPTION  "Entry Create failures" 
		::={ acosSlbRcCacheGlobalS 25 } 

		memSize OBJECT-TYPE
		SYNTAX  CounterBasedGauge64 
		MAX-ACCESS read-only 
		STATUS current
		DESCRIPTION  "Memory Used" 
		::={ acosSlbRcCacheGlobalS 26 } 

		entryNum OBJECT-TYPE
		SYNTAX  CounterBasedGauge64 
		MAX-ACCESS read-only 
		STATUS current
		DESCRIPTION  "Entry Cached" 
		::={ acosSlbRcCacheGlobalS 27 } 

		replacedEntry OBJECT-TYPE
		SYNTAX  CounterBasedGauge64 
		MAX-ACCESS read-only 
		STATUS current
		DESCRIPTION  "Entry Replaced" 
		::={ acosSlbRcCacheGlobalS 28 } 

		agingEntry OBJECT-TYPE
		SYNTAX  CounterBasedGauge64 
		MAX-ACCESS read-only 
		STATUS current
		DESCRIPTION  "Entry Aged Out" 
		::={ acosSlbRcCacheGlobalS 29 } 

		cleanedEntry OBJECT-TYPE
		SYNTAX  CounterBasedGauge64 
		MAX-ACCESS read-only 
		STATUS current
		DESCRIPTION  "Entry Cleaned" 
		::={ acosSlbRcCacheGlobalS 30 } 

		rspTypeStream OBJECT-TYPE
		SYNTAX  CounterBasedGauge64 
		MAX-ACCESS read-only 
		STATUS current
		DESCRIPTION  "Responses from http2 server 200 OK - Stream" 
		::={ acosSlbRcCacheGlobalS 31 } 

		rspBr OBJECT-TYPE
		SYNTAX  CounterBasedGauge64 
		MAX-ACCESS read-only 
		STATUS current
		DESCRIPTION  "Responses from cache 200 OK - Brotli" 
		::={ acosSlbRcCacheGlobalS 32 } 

acosSlbPlayerIdGlobal               OBJECT IDENTIFIER ::= { acosSlb 57 }
acosSlbPlayerIdGlobalS              OBJECT IDENTIFIER ::= { acosSlbPlayerIdGlobal 1 }

		totalPlayeridsCreated OBJECT-TYPE
		SYNTAX  CounterBasedGauge64 
		MAX-ACCESS read-only 
		STATUS current
		DESCRIPTION  "Playerid records created" 
		::={ acosSlbPlayerIdGlobalS 1 } 

		totalPlayeridsDeleted OBJECT-TYPE
		SYNTAX  CounterBasedGauge64 
		MAX-ACCESS read-only 
		STATUS current
		DESCRIPTION  "Playerid records deleted" 
		::={ acosSlbPlayerIdGlobalS 2 } 

		totalAbsMaxAgeOuts OBJECT-TYPE
		SYNTAX  CounterBasedGauge64 
		MAX-ACCESS read-only 
		STATUS current
		DESCRIPTION  "Playerid records max time aged out" 
		::={ acosSlbPlayerIdGlobalS 3 } 

		totalPktActivityAgeOuts OBJECT-TYPE
		SYNTAX  CounterBasedGauge64 
		MAX-ACCESS read-only 
		STATUS current
		DESCRIPTION  "Playerid records idle timeout" 
		::={ acosSlbPlayerIdGlobalS 4 } 

		totalInvalidPlayeridPkts OBJECT-TYPE
		SYNTAX  CounterBasedGauge64 
		MAX-ACCESS read-only 
		STATUS current
		DESCRIPTION  "Invalid playerid packets" 
		::={ acosSlbPlayerIdGlobalS 5 } 

		totalInvalidPlayeridDrops OBJECT-TYPE
		SYNTAX  CounterBasedGauge64 
		MAX-ACCESS read-only 
		STATUS current
		DESCRIPTION  "Invalid playerid packet drops" 
		::={ acosSlbPlayerIdGlobalS 6 } 

		totalValidPlayeridPkts OBJECT-TYPE
		SYNTAX  CounterBasedGauge64 
		MAX-ACCESS read-only 
		STATUS current
		DESCRIPTION  "Valid playerid packets" 
		::={ acosSlbPlayerIdGlobalS 7 } 

acosSlbSportRateLimit               OBJECT IDENTIFIER ::= { acosSlb 59 }
acosSlbSportRateLimitS              OBJECT IDENTIFIER ::= { acosSlbSportRateLimit 1 }

		allocSport OBJECT-TYPE
		SYNTAX  CounterBasedGauge64 
		MAX-ACCESS read-only 
		STATUS current
		DESCRIPTION  "Alloc'd src port entry" 
		::={ acosSlbSportRateLimitS 1 } 

		allocSportip OBJECT-TYPE
		SYNTAX  CounterBasedGauge64 
		MAX-ACCESS read-only 
		STATUS current
		DESCRIPTION  "Alloc'd src port-ip entry" 
		::={ acosSlbSportRateLimitS 2 } 

		freedSport OBJECT-TYPE
		SYNTAX  CounterBasedGauge64 
		MAX-ACCESS read-only 
		STATUS current
		DESCRIPTION  "Freed src port entry" 
		::={ acosSlbSportRateLimitS 3 } 

		freedSportip OBJECT-TYPE
		SYNTAX  CounterBasedGauge64 
		MAX-ACCESS read-only 
		STATUS current
		DESCRIPTION  "Freed src port-ip entry" 
		::={ acosSlbSportRateLimitS 4 } 

		totalDrop OBJECT-TYPE
		SYNTAX  CounterBasedGauge64 
		MAX-ACCESS read-only 
		STATUS current
		DESCRIPTION  "Total rate exceed drop" 
		::={ acosSlbSportRateLimitS 5 } 

		totalReset OBJECT-TYPE
		SYNTAX  CounterBasedGauge64 
		MAX-ACCESS read-only 
		STATUS current
		DESCRIPTION  "Total rate exceed reset" 
		::={ acosSlbSportRateLimitS 6 } 

		totalLog OBJECT-TYPE
		SYNTAX  CounterBasedGauge64 
		MAX-ACCESS read-only 
		STATUS current
		DESCRIPTION  "Total log sent" 
		::={ acosSlbSportRateLimitS 7 } 

acosSlbMlb                          OBJECT IDENTIFIER ::= { acosSlb 71 }
acosSlbMlbS                         OBJECT IDENTIFIER ::= { acosSlbMlb 1 }

		clientMsgSent OBJECT-TYPE
		SYNTAX  CounterBasedGauge64 
		MAX-ACCESS read-only 
		STATUS current
		DESCRIPTION  "Client message sent" 
		::={ acosSlbMlbS 1 } 

		serverMsgReceived OBJECT-TYPE
		SYNTAX  CounterBasedGauge64 
		MAX-ACCESS read-only 
		STATUS current
		DESCRIPTION  "Server message received" 
		::={ acosSlbMlbS 2 } 

		serverConnCreated OBJECT-TYPE
		SYNTAX  CounterBasedGauge64 
		MAX-ACCESS read-only 
		STATUS current
		DESCRIPTION  "Server connection created" 
		::={ acosSlbMlbS 3 } 

		serverConnRst OBJECT-TYPE
		SYNTAX  CounterBasedGauge64 
		MAX-ACCESS read-only 
		STATUS current
		DESCRIPTION  "Server connection reset" 
		::={ acosSlbMlbS 4 } 

		serverConnFailed OBJECT-TYPE
		SYNTAX  CounterBasedGauge64 
		MAX-ACCESS read-only 
		STATUS current
		DESCRIPTION  "Server connection failed" 
		::={ acosSlbMlbS 5 } 

		serverConnClosed OBJECT-TYPE
		SYNTAX  CounterBasedGauge64 
		MAX-ACCESS read-only 
		STATUS current
		DESCRIPTION  "Server connection closed" 
		::={ acosSlbMlbS 6 } 

		clientConnCreated OBJECT-TYPE
		SYNTAX  CounterBasedGauge64 
		MAX-ACCESS read-only 
		STATUS current
		DESCRIPTION  "Client connection created" 
		::={ acosSlbMlbS 7 } 

		clientConnClosed OBJECT-TYPE
		SYNTAX  CounterBasedGauge64 
		MAX-ACCESS read-only 
		STATUS current
		DESCRIPTION  "Client connection closed" 
		::={ acosSlbMlbS 8 } 

		clientConnNotFound OBJECT-TYPE
		SYNTAX  CounterBasedGauge64 
		MAX-ACCESS read-only 
		STATUS current
		DESCRIPTION  "Client connection not found" 
		::={ acosSlbMlbS 9 } 

		msgDropped OBJECT-TYPE
		SYNTAX  CounterBasedGauge64 
		MAX-ACCESS read-only 
		STATUS current
		DESCRIPTION  "Message dropped" 
		::={ acosSlbMlbS 10 } 

		msgRerouted OBJECT-TYPE
		SYNTAX  CounterBasedGauge64 
		MAX-ACCESS read-only 
		STATUS current
		DESCRIPTION  "Message rerouted" 
		::={ acosSlbMlbS 11 } 

		mlbDcmsgSent OBJECT-TYPE
		SYNTAX  CounterBasedGauge64 
		MAX-ACCESS read-only 
		STATUS current
		DESCRIPTION  "Dcmsg sent" 
		::={ acosSlbMlbS 12 } 

		mlbDcmsgReceived OBJECT-TYPE
		SYNTAX  CounterBasedGauge64 
		MAX-ACCESS read-only 
		STATUS current
		DESCRIPTION  "Dcmsg received" 
		::={ acosSlbMlbS 13 } 

		mlbDcmsgError OBJECT-TYPE
		SYNTAX  CounterBasedGauge64 
		MAX-ACCESS read-only 
		STATUS current
		DESCRIPTION  "Dcmsg error" 
		::={ acosSlbMlbS 14 } 

		mlbDcmsgAlloc OBJECT-TYPE
		SYNTAX  CounterBasedGauge64 
		MAX-ACCESS read-only 
		STATUS current
		DESCRIPTION  "Dcmsg alloc" 
		::={ acosSlbMlbS 15 } 

		mlbDcmsgFree OBJECT-TYPE
		SYNTAX  CounterBasedGauge64 
		MAX-ACCESS read-only 
		STATUS current
		DESCRIPTION  "Dcmsg free" 
		::={ acosSlbMlbS 16 } 

		mlbServerProbe OBJECT-TYPE
		SYNTAX  CounterBasedGauge64 
		MAX-ACCESS read-only 
		STATUS current
		DESCRIPTION  "Server probe" 
		::={ acosSlbMlbS 17 } 

		mlbServerDown OBJECT-TYPE
		SYNTAX  CounterBasedGauge64 
		MAX-ACCESS read-only 
		STATUS current
		DESCRIPTION  "Server down" 
		::={ acosSlbMlbS 18 } 

acosSlbDnsResponseRateLimiting      OBJECT IDENTIFIER ::= { acosSlb 75 }
acosSlbDnsResponseRateLimitingS     OBJECT IDENTIFIER ::= { acosSlbDnsResponseRateLimiting 1 }

		currEntries OBJECT-TYPE
		SYNTAX  CounterBasedGauge64 
		MAX-ACCESS read-only 
		STATUS current
		DESCRIPTION  "Current Entry Count" 
		::={ acosSlbDnsResponseRateLimitingS 1 } 

		totalCreated OBJECT-TYPE
		SYNTAX  CounterBasedGauge64 
		MAX-ACCESS read-only 
		STATUS current
		DESCRIPTION  "Total Entry Created" 
		::={ acosSlbDnsResponseRateLimitingS 2 } 

		totalInserted OBJECT-TYPE
		SYNTAX  CounterBasedGauge64 
		MAX-ACCESS read-only 
		STATUS current
		DESCRIPTION  "Total Entry Inserted" 
		::={ acosSlbDnsResponseRateLimitingS 3 } 

		totalWithdrew OBJECT-TYPE
		SYNTAX  CounterBasedGauge64 
		MAX-ACCESS read-only 
		STATUS current
		DESCRIPTION  "Total Entry Withdrew" 
		::={ acosSlbDnsResponseRateLimitingS 4 } 

		totalReadyToFree OBJECT-TYPE
		SYNTAX  CounterBasedGauge64 
		MAX-ACCESS read-only 
		STATUS current
		DESCRIPTION  "Total Entry Ready To Free" 
		::={ acosSlbDnsResponseRateLimitingS 5 } 

		totalFreed OBJECT-TYPE
		SYNTAX  CounterBasedGauge64 
		MAX-ACCESS read-only 
		STATUS current
		DESCRIPTION  "Total Entry Freed" 
		::={ acosSlbDnsResponseRateLimitingS 6 } 

		totalLogs OBJECT-TYPE
		SYNTAX  CounterBasedGauge64 
		MAX-ACCESS read-only 
		STATUS current
		DESCRIPTION  "Total Logs" 
		::={ acosSlbDnsResponseRateLimitingS 7 } 

		totalOverflowEntryHits OBJECT-TYPE
		SYNTAX  CounterBasedGauge64 
		MAX-ACCESS read-only 
		STATUS current
		DESCRIPTION  "Total Overflow Entry Hits" 
		::={ acosSlbDnsResponseRateLimitingS 8 } 

		totalRefill OBJECT-TYPE
		SYNTAX  CounterBasedGauge64 
		MAX-ACCESS read-only 
		STATUS current
		DESCRIPTION  "Total Refills" 
		::={ acosSlbDnsResponseRateLimitingS 9 } 

		totalCreditExceeded OBJECT-TYPE
		SYNTAX  CounterBasedGauge64 
		MAX-ACCESS read-only 
		STATUS current
		DESCRIPTION  "Total Credit Exceeded" 
		::={ acosSlbDnsResponseRateLimitingS 10 } 

		otherThreadRefill OBJECT-TYPE
		SYNTAX  CounterBasedGauge64 
		MAX-ACCESS read-only 
		STATUS current
		DESCRIPTION  "Other Thread Refilling" 
		::={ acosSlbDnsResponseRateLimitingS 11 } 

		errEntryCreateFailed OBJECT-TYPE
		SYNTAX  CounterBasedGauge64 
		MAX-ACCESS read-only 
		STATUS current
		DESCRIPTION  "Entry Creation Failure" 
		::={ acosSlbDnsResponseRateLimitingS 12 } 

		errEntryCreateOom OBJECT-TYPE
		SYNTAX  CounterBasedGauge64 
		MAX-ACCESS read-only 
		STATUS current
		DESCRIPTION  "Entry Creation Out of Memory" 
		::={ acosSlbDnsResponseRateLimitingS 13 } 

		errEntryExtCreateOom OBJECT-TYPE
		SYNTAX  CounterBasedGauge64 
		MAX-ACCESS read-only 
		STATUS current
		DESCRIPTION  "Entry Extension Creation Out of Memory" 
		::={ acosSlbDnsResponseRateLimitingS 14 } 

		errEntryInsertFailed OBJECT-TYPE
		SYNTAX  CounterBasedGauge64 
		MAX-ACCESS read-only 
		STATUS current
		DESCRIPTION  "Entry Insert Failed" 
		::={ acosSlbDnsResponseRateLimitingS 15 } 

		errVportFailMatch OBJECT-TYPE
		SYNTAX  CounterBasedGauge64 
		MAX-ACCESS read-only 
		STATUS current
		DESCRIPTION  "Failed to Match Vport" 
		::={ acosSlbDnsResponseRateLimitingS 16 } 

acosSlbLinkProbe                    OBJECT IDENTIFIER ::= { acosSlb 78 }
acosSlbLinkProbeEntry               OBJECT IDENTIFIER ::= { acosSlbLinkProbe 1 }
acosSlbLinkProbeEntryS              OBJECT IDENTIFIER ::= { acosSlbLinkProbeEntry 1 }

		currEntries OBJECT-TYPE
		SYNTAX  CounterBasedGauge64 
		MAX-ACCESS read-only 
		STATUS current
		DESCRIPTION  "Current Entry Count" 
		::={ acosSlbLinkProbeEntryS 1 } 

		totalCreated OBJECT-TYPE
		SYNTAX  CounterBasedGauge64 
		MAX-ACCESS read-only 
		STATUS current
		DESCRIPTION  "Total Entry Created" 
		::={ acosSlbLinkProbeEntryS 2 } 

		totalInserted OBJECT-TYPE
		SYNTAX  CounterBasedGauge64 
		MAX-ACCESS read-only 
		STATUS current
		DESCRIPTION  "Total Entry Inserted" 
		::={ acosSlbLinkProbeEntryS 3 } 

		totalReadyToFree OBJECT-TYPE
		SYNTAX  CounterBasedGauge64 
		MAX-ACCESS read-only 
		STATUS current
		DESCRIPTION  "Total Entry Ready To Free" 
		::={ acosSlbLinkProbeEntryS 4 } 

		totalFreed OBJECT-TYPE
		SYNTAX  CounterBasedGauge64 
		MAX-ACCESS read-only 
		STATUS current
		DESCRIPTION  "Total Entry Freed" 
		::={ acosSlbLinkProbeEntryS 5 } 

		errEntryCreateFailed OBJECT-TYPE
		SYNTAX  CounterBasedGauge64 
		MAX-ACCESS read-only 
		STATUS current
		DESCRIPTION  "Entry Creation Failure" 
		::={ acosSlbLinkProbeEntryS 6 } 

		errEntryCreateOom OBJECT-TYPE
		SYNTAX  CounterBasedGauge64 
		MAX-ACCESS read-only 
		STATUS current
		DESCRIPTION  "Entry Creation Out of Memory" 
		::={ acosSlbLinkProbeEntryS 7 } 

		errEntryInsertFailed OBJECT-TYPE
		SYNTAX  CounterBasedGauge64 
		MAX-ACCESS read-only 
		STATUS current
		DESCRIPTION  "Entry Insert Failed" 
		::={ acosSlbLinkProbeEntryS 8 } 

		errTmplProbeCreateFailed OBJECT-TYPE
		SYNTAX  CounterBasedGauge64 
		MAX-ACCESS read-only 
		STATUS current
		DESCRIPTION  "Probe Template Creation Failure" 
		::={ acosSlbLinkProbeEntryS 9 } 

		errTmplProbeCreateOom OBJECT-TYPE
		SYNTAX  CounterBasedGauge64 
		MAX-ACCESS read-only 
		STATUS current
		DESCRIPTION  "Probe Template Creation Out of Memory" 
		::={ acosSlbLinkProbeEntryS 10 } 

		totalHttpProbesSent OBJECT-TYPE
		SYNTAX  CounterBasedGauge64 
		MAX-ACCESS read-only 
		STATUS current
		DESCRIPTION  "Total HTTP Probes Sent out" 
		::={ acosSlbLinkProbeEntryS 11 } 

		totalHttpResponseReceived OBJECT-TYPE
		SYNTAX  CounterBasedGauge64 
		MAX-ACCESS read-only 
		STATUS current
		DESCRIPTION  "Total HTTP responses received" 
		::={ acosSlbLinkProbeEntryS 12 } 

		totalHttpResponseGood OBJECT-TYPE
		SYNTAX  CounterBasedGauge64 
		MAX-ACCESS read-only 
		STATUS current
		DESCRIPTION  "Total HTTP responses matching probe template config" 
		::={ acosSlbLinkProbeEntryS 13 } 

		totalHttpResponseBad OBJECT-TYPE
		SYNTAX  CounterBasedGauge64 
		MAX-ACCESS read-only 
		STATUS current
		DESCRIPTION  "Total HTTP responses not matching probe template config" 
		::={ acosSlbLinkProbeEntryS 14 } 

		totalTcpErr OBJECT-TYPE
		SYNTAX  CounterBasedGauge64 
		MAX-ACCESS read-only 
		STATUS current
		DESCRIPTION  "Total TCP errors in probes sent out" 
		::={ acosSlbLinkProbeEntryS 15 } 

		errSmartNatAlloc OBJECT-TYPE
		SYNTAX  CounterBasedGauge64 
		MAX-ACCESS read-only 
		STATUS current
		DESCRIPTION  "Error creating Smart NAT Instance" 
		::={ acosSlbLinkProbeEntryS 16 } 

		errSmartNatPortAlloc OBJECT-TYPE
		SYNTAX  CounterBasedGauge64 
		MAX-ACCESS read-only 
		STATUS current
		DESCRIPTION  "Error obtaining Smart NAT source port" 
		::={ acosSlbLinkProbeEntryS 17 } 

		errL4SessAlloc OBJECT-TYPE
		SYNTAX  CounterBasedGauge64 
		MAX-ACCESS read-only 
		STATUS current
		DESCRIPTION  "Error allocating L4 session for probe" 
		::={ acosSlbLinkProbeEntryS 18 } 

		errProbeTcpConnSend OBJECT-TYPE
		SYNTAX  CounterBasedGauge64 
		MAX-ACCESS read-only 
		STATUS current
		DESCRIPTION  "Error in initiating TCP connection for probe" 
		::={ acosSlbLinkProbeEntryS 19 } 

		probeTcpConnSent OBJECT-TYPE
		SYNTAX  CounterBasedGauge64 
		MAX-ACCESS read-only 
		STATUS current
		DESCRIPTION  "TCP connection sent for probe" 
		::={ acosSlbLinkProbeEntryS 20 } 

acosSlbHmDplane                     OBJECT IDENTIFIER ::= { acosSlb 105 }
acosSlbHmDplaneS                    OBJECT IDENTIFIER ::= { acosSlbHmDplane 1 }

		currEntries OBJECT-TYPE
		SYNTAX  CounterBasedGauge64 
		MAX-ACCESS read-only 
		STATUS current
		DESCRIPTION  "Current HM Entries" 
		::={ acosSlbHmDplaneS 1 } 

		totalCreated OBJECT-TYPE
		SYNTAX  CounterBasedGauge64 
		MAX-ACCESS read-only 
		STATUS current
		DESCRIPTION  "Total HM Entries Created" 
		::={ acosSlbHmDplaneS 2 } 

		totalInserted OBJECT-TYPE
		SYNTAX  CounterBasedGauge64 
		MAX-ACCESS read-only 
		STATUS current
		DESCRIPTION  "Total HM entries inserted" 
		::={ acosSlbHmDplaneS 3 } 

		totalReadyToFree OBJECT-TYPE
		SYNTAX  CounterBasedGauge64 
		MAX-ACCESS read-only 
		STATUS current
		DESCRIPTION  "Total HM entries ready to free" 
		::={ acosSlbHmDplaneS 4 } 

		totalFreed OBJECT-TYPE
		SYNTAX  CounterBasedGauge64 
		MAX-ACCESS read-only 
		STATUS current
		DESCRIPTION  "Total HM entries freed" 
		::={ acosSlbHmDplaneS 5 } 

		errEntryCreateFailed OBJECT-TYPE
		SYNTAX  CounterBasedGauge64 
		MAX-ACCESS read-only 
		STATUS current
		DESCRIPTION  "Entry Creation Failure" 
		::={ acosSlbHmDplaneS 6 } 

		errEntryCreateOom OBJECT-TYPE
		SYNTAX  CounterBasedGauge64 
		MAX-ACCESS read-only 
		STATUS current
		DESCRIPTION  "Entry creation out of memory" 
		::={ acosSlbHmDplaneS 7 } 

		errEntryInsertFailed OBJECT-TYPE
		SYNTAX  CounterBasedGauge64 
		MAX-ACCESS read-only 
		STATUS current
		DESCRIPTION  "Entry insert failed" 
		::={ acosSlbHmDplaneS 8 } 

		totalTcpErr OBJECT-TYPE
		SYNTAX  CounterBasedGauge64 
		MAX-ACCESS read-only 
		STATUS current
		DESCRIPTION  "Total TCP errors in health-checks sent" 
		::={ acosSlbHmDplaneS 15 } 

		errSmartNatAlloc OBJECT-TYPE
		SYNTAX  CounterBasedGauge64 
		MAX-ACCESS read-only 
		STATUS current
		DESCRIPTION  "Error creating smart-nat instance" 
		::={ acosSlbHmDplaneS 16 } 

		errSmartNatPortAlloc OBJECT-TYPE
		SYNTAX  CounterBasedGauge64 
		MAX-ACCESS read-only 
		STATUS current
		DESCRIPTION  "Error obtaining smart-nat source port" 
		::={ acosSlbHmDplaneS 17 } 

		errL4SessAlloc OBJECT-TYPE
		SYNTAX  CounterBasedGauge64 
		MAX-ACCESS read-only 
		STATUS current
		DESCRIPTION  "Error allocating L4 session for HM" 
		::={ acosSlbHmDplaneS 18 } 

		errHmTcpConnSent OBJECT-TYPE
		SYNTAX  CounterBasedGauge64 
		MAX-ACCESS read-only 
		STATUS current
		DESCRIPTION  "Error in initiating TCP connection for HM" 
		::={ acosSlbHmDplaneS 19 } 

		hmTcpConnSent OBJECT-TYPE
		SYNTAX  CounterBasedGauge64 
		MAX-ACCESS read-only 
		STATUS current
		DESCRIPTION  "Total TCP connections sent for HM" 
		::={ acosSlbHmDplaneS 20 } 

		entryDeleted OBJECT-TYPE
		SYNTAX  CounterBasedGauge64 
		MAX-ACCESS read-only 
		STATUS current
		DESCRIPTION  "Entry deleted" 
		::={ acosSlbHmDplaneS 21 } 

		errEntryCreateSlbFailed OBJECT-TYPE
		SYNTAX  CounterBasedGauge64 
		MAX-ACCESS read-only 
		STATUS current
		DESCRIPTION  "Error in creating HM internal SLB Resource" 
		::={ acosSlbHmDplaneS 22 } 

		totalMatchRespCode OBJECT-TYPE
		SYNTAX  CounterBasedGauge64 
		MAX-ACCESS read-only 
		STATUS current
		DESCRIPTION  "Total HTTP received response with match response code" 
		::={ acosSlbHmDplaneS 23 } 

		totalMatchDefaultRespCode OBJECT-TYPE
		SYNTAX  CounterBasedGauge64 
		MAX-ACCESS read-only 
		STATUS current
		DESCRIPTION  "Total HTTP received response with match 200 response code" 
		::={ acosSlbHmDplaneS 24 } 

		totalMaintenanceReceived OBJECT-TYPE
		SYNTAX  CounterBasedGauge64 
		MAX-ACCESS read-only 
		STATUS current
		DESCRIPTION  "Total maintenace response received" 
		::={ acosSlbHmDplaneS 25 } 

		totalWrongStatusReceived OBJECT-TYPE
		SYNTAX  CounterBasedGauge64 
		MAX-ACCESS read-only 
		STATUS current
		DESCRIPTION  "Total HTTP received response with wrong response code" 
		::={ acosSlbHmDplaneS 26 } 

		errNoHmEntry OBJECT-TYPE
		SYNTAX  CounterBasedGauge64 
		MAX-ACCESS read-only 
		STATUS current
		DESCRIPTION  "Error no HM entry found" 
		::={ acosSlbHmDplaneS 27 } 

		errSslCertNameMismatch OBJECT-TYPE
		SYNTAX  CounterBasedGauge64 
		MAX-ACCESS read-only 
		STATUS current
		DESCRIPTION  "Error SSL cert name mismatch" 
		::={ acosSlbHmDplaneS 28 } 

		errServerSynTimeout OBJECT-TYPE
		SYNTAX  CounterBasedGauge64 
		MAX-ACCESS read-only 
		STATUS current
		DESCRIPTION  "Error SSL server SYN timeout" 
		::={ acosSlbHmDplaneS 29 } 

		errHttp2Callback OBJECT-TYPE
		SYNTAX  CounterBasedGauge64 
		MAX-ACCESS read-only 
		STATUS current
		DESCRIPTION  "Error HTTP2 callback" 
		::={ acosSlbHmDplaneS 30 } 

		errL7SessProcessTcpEstabFailed OBJECT-TYPE
		SYNTAX  CounterBasedGauge64 
		MAX-ACCESS read-only 
		STATUS current
		DESCRIPTION  "L7 session process TCP established failed" 
		::={ acosSlbHmDplaneS 31 } 

		errL7SessProcessTcpDataFailed OBJECT-TYPE
		SYNTAX  CounterBasedGauge64 
		MAX-ACCESS read-only 
		STATUS current
		DESCRIPTION  "L7 session process TCP data failed" 
		::={ acosSlbHmDplaneS 32 } 

		errHttp2VerMismatch OBJECT-TYPE
		SYNTAX  CounterBasedGauge64 
		MAX-ACCESS read-only 
		STATUS current
		DESCRIPTION  "Error HTTP2 version mismatch" 
		::={ acosSlbHmDplaneS 33 } 

		smartNatAlloc OBJECT-TYPE
		SYNTAX  CounterBasedGauge64 
		MAX-ACCESS read-only 
		STATUS current
		DESCRIPTION  "Total smart-nat allocation successful" 
		::={ acosSlbHmDplaneS 34 } 

		smartNatRelease OBJECT-TYPE
		SYNTAX  CounterBasedGauge64 
		MAX-ACCESS read-only 
		STATUS current
		DESCRIPTION  "Total smart-nat release successful" 
		::={ acosSlbHmDplaneS 35 } 

		smartNatAllocFailed OBJECT-TYPE
		SYNTAX  CounterBasedGauge64 
		MAX-ACCESS read-only 
		STATUS current
		DESCRIPTION  "Total smart-nat allocation failed" 
		::={ acosSlbHmDplaneS 36 } 

		smartNatReleaseFailed OBJECT-TYPE
		SYNTAX  CounterBasedGauge64 
		MAX-ACCESS read-only 
		STATUS current
		DESCRIPTION  "Total smart-nat release failed" 
		::={ acosSlbHmDplaneS 37 } 

		totalServerQuicConn OBJECT-TYPE
		SYNTAX  CounterBasedGauge64 
		MAX-ACCESS read-only 
		STATUS current
		DESCRIPTION  "Total start server QUIC connections" 
		::={ acosSlbHmDplaneS 38 } 

		totalServerQuicConnErr OBJECT-TYPE
		SYNTAX  CounterBasedGauge64 
		MAX-ACCESS read-only 
		STATUS current
		DESCRIPTION  "Total start server QUIC connections error" 
		::={ acosSlbHmDplaneS 39 } 

		totalStartServerConnErr OBJECT-TYPE
		SYNTAX  CounterBasedGauge64 
		MAX-ACCESS read-only 
		STATUS current
		DESCRIPTION  "Total start server connections error" 
		::={ acosSlbHmDplaneS 40 } 

		errMissingServerSslTemplate OBJECT-TYPE
		SYNTAX  CounterBasedGauge64 
		MAX-ACCESS read-only 
		STATUS current
		DESCRIPTION  "Missing Server-SSL Template" 
		::={ acosSlbHmDplaneS 41 } 

		errCreateSslCtxFail OBJECT-TYPE
		SYNTAX  CounterBasedGauge64 
		MAX-ACCESS read-only 
		STATUS current
		DESCRIPTION  "Error in creating SSL CTX" 
		::={ acosSlbHmDplaneS 42 } 

		errEntryMissingVport OBJECT-TYPE
		SYNTAX  CounterBasedGauge64 
		MAX-ACCESS read-only 
		STATUS current
		DESCRIPTION  "Entry missing Virtual-Port" 
		::={ acosSlbHmDplaneS 43 } 

acosSlbRpz                          OBJECT IDENTIFIER ::= { acosSlb 89 }
acosSlbRpzS                         OBJECT IDENTIFIER ::= { acosSlbRpz 1 }

		setBwError OBJECT-TYPE
		SYNTAX  CounterBasedGauge64 
		MAX-ACCESS read-only 
		STATUS current
		DESCRIPTION  "Total RPZ Set Class-list Error" 
		::={ acosSlbRpzS 1 } 

		parseError OBJECT-TYPE
		SYNTAX  CounterBasedGauge64 
		MAX-ACCESS read-only 
		STATUS current
		DESCRIPTION  "Total RPZ Parse Error" 
		::={ acosSlbRpzS 2 } 

acosSlbQuic                         OBJECT IDENTIFIER ::= { acosSlb 108 }
acosSlbQuicS                        OBJECT IDENTIFIER ::= { acosSlbQuic 1 }

		clientConnAttempted OBJECT-TYPE
		SYNTAX  CounterBasedGauge64 
		MAX-ACCESS read-only 
		STATUS current
		DESCRIPTION  "Client connection attempted" 
		::={ acosSlbQuicS 1 } 

		clientConnHandshake OBJECT-TYPE
		SYNTAX  CounterBasedGauge64 
		MAX-ACCESS read-only 
		STATUS current
		DESCRIPTION  "Client connection handshake" 
		::={ acosSlbQuicS 2 } 

		clientConnCreated OBJECT-TYPE
		SYNTAX  CounterBasedGauge64 
		MAX-ACCESS read-only 
		STATUS current
		DESCRIPTION  "Client connection created" 
		::={ acosSlbQuicS 3 } 

		clientConnLocalClosed OBJECT-TYPE
		SYNTAX  CounterBasedGauge64 
		MAX-ACCESS read-only 
		STATUS current
		DESCRIPTION  "Client connection local closed" 
		::={ acosSlbQuicS 4 } 

		clientConnRemoteClosed OBJECT-TYPE
		SYNTAX  CounterBasedGauge64 
		MAX-ACCESS read-only 
		STATUS current
		DESCRIPTION  "Client connection remote closed" 
		::={ acosSlbQuicS 5 } 

		clientConnFailed OBJECT-TYPE
		SYNTAX  CounterBasedGauge64 
		MAX-ACCESS read-only 
		STATUS current
		DESCRIPTION  "Client connection failed" 
		::={ acosSlbQuicS 6 } 

		serverConnAttempted OBJECT-TYPE
		SYNTAX  CounterBasedGauge64 
		MAX-ACCESS read-only 
		STATUS current
		DESCRIPTION  "Server connection attempted" 
		::={ acosSlbQuicS 7 } 

		serverConnHandshake OBJECT-TYPE
		SYNTAX  CounterBasedGauge64 
		MAX-ACCESS read-only 
		STATUS current
		DESCRIPTION  "Server connection handshake" 
		::={ acosSlbQuicS 8 } 

		serverConnCreated OBJECT-TYPE
		SYNTAX  CounterBasedGauge64 
		MAX-ACCESS read-only 
		STATUS current
		DESCRIPTION  "Server connection created" 
		::={ acosSlbQuicS 9 } 

		serverConnLocalClosed OBJECT-TYPE
		SYNTAX  CounterBasedGauge64 
		MAX-ACCESS read-only 
		STATUS current
		DESCRIPTION  "Server connection local closed" 
		::={ acosSlbQuicS 10 } 

		serverConnRemoteClosed OBJECT-TYPE
		SYNTAX  CounterBasedGauge64 
		MAX-ACCESS read-only 
		STATUS current
		DESCRIPTION  "Server connection remote closed" 
		::={ acosSlbQuicS 11 } 

		serverConnFailed OBJECT-TYPE
		SYNTAX  CounterBasedGauge64 
		MAX-ACCESS read-only 
		STATUS current
		DESCRIPTION  "Server connection failed" 
		::={ acosSlbQuicS 12 } 

		qConnCreated OBJECT-TYPE
		SYNTAX  CounterBasedGauge64 
		MAX-ACCESS read-only 
		STATUS current
		DESCRIPTION  "Q connection created" 
		::={ acosSlbQuicS 168 } 

		qConnFreed OBJECT-TYPE
		SYNTAX  CounterBasedGauge64 
		MAX-ACCESS read-only 
		STATUS current
		DESCRIPTION  "Q connection freed" 
		::={ acosSlbQuicS 169 } 

		localBiStreamCurrent OBJECT-TYPE
		SYNTAX  CounterBasedGauge64 
		MAX-ACCESS read-only 
		STATUS current
		DESCRIPTION  "Current local bi-stream" 
		::={ acosSlbQuicS 227 } 

		remoteBiStreamCurrent OBJECT-TYPE
		SYNTAX  CounterBasedGauge64 
		MAX-ACCESS read-only 
		STATUS current
		DESCRIPTION  "Current remote bi-stream" 
		::={ acosSlbQuicS 228 } 

		localBiStreamCreated OBJECT-TYPE
		SYNTAX  CounterBasedGauge64 
		MAX-ACCESS read-only 
		STATUS current
		DESCRIPTION  "Local bi-stream created" 
		::={ acosSlbQuicS 20 } 

		remoteBiStreamCreated OBJECT-TYPE
		SYNTAX  CounterBasedGauge64 
		MAX-ACCESS read-only 
		STATUS current
		DESCRIPTION  "Remote bi-stream created" 
		::={ acosSlbQuicS 21 } 

		localBiStreamClosed OBJECT-TYPE
		SYNTAX  CounterBasedGauge64 
		MAX-ACCESS read-only 
		STATUS current
		DESCRIPTION  "Local bi-stream closed" 
		::={ acosSlbQuicS 22 } 

		remoteBiStreamClosed OBJECT-TYPE
		SYNTAX  CounterBasedGauge64 
		MAX-ACCESS read-only 
		STATUS current
		DESCRIPTION  "Remote bi-stream closed" 
		::={ acosSlbQuicS 182 } 

		localUniStreamCurrent OBJECT-TYPE
		SYNTAX  CounterBasedGauge64 
		MAX-ACCESS read-only 
		STATUS current
		DESCRIPTION  "Current local uni-stream" 
		::={ acosSlbQuicS 229 } 

		remoteUniStreamCurrent OBJECT-TYPE
		SYNTAX  CounterBasedGauge64 
		MAX-ACCESS read-only 
		STATUS current
		DESCRIPTION  "Current remote uni-stream" 
		::={ acosSlbQuicS 230 } 

		localUniStreamCreated OBJECT-TYPE
		SYNTAX  CounterBasedGauge64 
		MAX-ACCESS read-only 
		STATUS current
		DESCRIPTION  "Local uni-stream created" 
		::={ acosSlbQuicS 23 } 

		remoteUniStreamCreated OBJECT-TYPE
		SYNTAX  CounterBasedGauge64 
		MAX-ACCESS read-only 
		STATUS current
		DESCRIPTION  "Remote uni-stream created" 
		::={ acosSlbQuicS 24 } 

		localUniStreamClosed OBJECT-TYPE
		SYNTAX  CounterBasedGauge64 
		MAX-ACCESS read-only 
		STATUS current
		DESCRIPTION  "Local uni-stream closed" 
		::={ acosSlbQuicS 25 } 

		remoteUniStreamClosed OBJECT-TYPE
		SYNTAX  CounterBasedGauge64 
		MAX-ACCESS read-only 
		STATUS current
		DESCRIPTION  "Remote uni-stream closed" 
		::={ acosSlbQuicS 183 } 

		streamError OBJECT-TYPE
		SYNTAX  CounterBasedGauge64 
		MAX-ACCESS read-only 
		STATUS current
		DESCRIPTION  "Stream error" 
		::={ acosSlbQuicS 26 } 

		streamFailToInsert OBJECT-TYPE
		SYNTAX  CounterBasedGauge64 
		MAX-ACCESS read-only 
		STATUS current
		DESCRIPTION  "Stream fail to insert" 
		::={ acosSlbQuicS 226 } 

		paddingFrameRx OBJECT-TYPE
		SYNTAX  CounterBasedGauge64 
		MAX-ACCESS read-only 
		STATUS current
		DESCRIPTION  "padding frame receive" 
		::={ acosSlbQuicS 30 } 

		paddingFrameTx OBJECT-TYPE
		SYNTAX  CounterBasedGauge64 
		MAX-ACCESS read-only 
		STATUS current
		DESCRIPTION  "padding frame send" 
		::={ acosSlbQuicS 31 } 

		pingFrameRx OBJECT-TYPE
		SYNTAX  CounterBasedGauge64 
		MAX-ACCESS read-only 
		STATUS current
		DESCRIPTION  "ping frame receive" 
		::={ acosSlbQuicS 32 } 

		pingFrameTx OBJECT-TYPE
		SYNTAX  CounterBasedGauge64 
		MAX-ACCESS read-only 
		STATUS current
		DESCRIPTION  "ping frame send" 
		::={ acosSlbQuicS 33 } 

		ackFrameRx OBJECT-TYPE
		SYNTAX  CounterBasedGauge64 
		MAX-ACCESS read-only 
		STATUS current
		DESCRIPTION  "ack frame receive" 
		::={ acosSlbQuicS 34 } 

		ackFrameTx OBJECT-TYPE
		SYNTAX  CounterBasedGauge64 
		MAX-ACCESS read-only 
		STATUS current
		DESCRIPTION  "ack frame send" 
		::={ acosSlbQuicS 35 } 

		ackEcnFrameRx OBJECT-TYPE
		SYNTAX  CounterBasedGauge64 
		MAX-ACCESS read-only 
		STATUS current
		DESCRIPTION  "ack enc frame receive" 
		::={ acosSlbQuicS 36 } 

		ackEcnFrameTx OBJECT-TYPE
		SYNTAX  CounterBasedGauge64 
		MAX-ACCESS read-only 
		STATUS current
		DESCRIPTION  "ack enc frame send" 
		::={ acosSlbQuicS 37 } 

		streamRstFrameRx OBJECT-TYPE
		SYNTAX  CounterBasedGauge64 
		MAX-ACCESS read-only 
		STATUS current
		DESCRIPTION  "stream reset frame receive" 
		::={ acosSlbQuicS 38 } 

		streamRstFrameTx OBJECT-TYPE
		SYNTAX  CounterBasedGauge64 
		MAX-ACCESS read-only 
		STATUS current
		DESCRIPTION  "stream reset frame send" 
		::={ acosSlbQuicS 39 } 

		streamStopFrameRx OBJECT-TYPE
		SYNTAX  CounterBasedGauge64 
		MAX-ACCESS read-only 
		STATUS current
		DESCRIPTION  "stream stop frame receive" 
		::={ acosSlbQuicS 40 } 

		streamStopFrameTx OBJECT-TYPE
		SYNTAX  CounterBasedGauge64 
		MAX-ACCESS read-only 
		STATUS current
		DESCRIPTION  "stream stop frame send" 
		::={ acosSlbQuicS 41 } 

		cryptoFrameRx OBJECT-TYPE
		SYNTAX  CounterBasedGauge64 
		MAX-ACCESS read-only 
		STATUS current
		DESCRIPTION  "crypto frame receive" 
		::={ acosSlbQuicS 42 } 

		cryptoFrameTx OBJECT-TYPE
		SYNTAX  CounterBasedGauge64 
		MAX-ACCESS read-only 
		STATUS current
		DESCRIPTION  "crypto frame send" 
		::={ acosSlbQuicS 43 } 

		newTokenFrameRx OBJECT-TYPE
		SYNTAX  CounterBasedGauge64 
		MAX-ACCESS read-only 
		STATUS current
		DESCRIPTION  "new token frame receive" 
		::={ acosSlbQuicS 44 } 

		newTokenFrameTx OBJECT-TYPE
		SYNTAX  CounterBasedGauge64 
		MAX-ACCESS read-only 
		STATUS current
		DESCRIPTION  "new token frame send" 
		::={ acosSlbQuicS 45 } 

		streamFrameRx OBJECT-TYPE
		SYNTAX  CounterBasedGauge64 
		MAX-ACCESS read-only 
		STATUS current
		DESCRIPTION  "stream frame receive" 
		::={ acosSlbQuicS 46 } 

		streamFrameTx OBJECT-TYPE
		SYNTAX  CounterBasedGauge64 
		MAX-ACCESS read-only 
		STATUS current
		DESCRIPTION  "stream frame send" 
		::={ acosSlbQuicS 47 } 

		stream09FrameRx OBJECT-TYPE
		SYNTAX  CounterBasedGauge64 
		MAX-ACCESS read-only 
		STATUS current
		DESCRIPTION  "stream 09 frame receive" 
		::={ acosSlbQuicS 48 } 

		stream09FrameTx OBJECT-TYPE
		SYNTAX  CounterBasedGauge64 
		MAX-ACCESS read-only 
		STATUS current
		DESCRIPTION  "stream 09 frame send" 
		::={ acosSlbQuicS 49 } 

		stream0aFrameRx OBJECT-TYPE
		SYNTAX  CounterBasedGauge64 
		MAX-ACCESS read-only 
		STATUS current
		DESCRIPTION  "stream 0a frame receive" 
		::={ acosSlbQuicS 50 } 

		stream0aFrameTx OBJECT-TYPE
		SYNTAX  CounterBasedGauge64 
		MAX-ACCESS read-only 
		STATUS current
		DESCRIPTION  "stream 0a frame send" 
		::={ acosSlbQuicS 51 } 

		stream0bFrameRx OBJECT-TYPE
		SYNTAX  CounterBasedGauge64 
		MAX-ACCESS read-only 
		STATUS current
		DESCRIPTION  "stream 0b frame receive" 
		::={ acosSlbQuicS 52 } 

		stream0bFrameTx OBJECT-TYPE
		SYNTAX  CounterBasedGauge64 
		MAX-ACCESS read-only 
		STATUS current
		DESCRIPTION  "stream 0b frame send" 
		::={ acosSlbQuicS 53 } 

		stream0cFrameRx OBJECT-TYPE
		SYNTAX  CounterBasedGauge64 
		MAX-ACCESS read-only 
		STATUS current
		DESCRIPTION  "stream 0c frame receive" 
		::={ acosSlbQuicS 54 } 

		stream0cFrameTx OBJECT-TYPE
		SYNTAX  CounterBasedGauge64 
		MAX-ACCESS read-only 
		STATUS current
		DESCRIPTION  "stream 0c frame send" 
		::={ acosSlbQuicS 55 } 

		stream0dFrameRx OBJECT-TYPE
		SYNTAX  CounterBasedGauge64 
		MAX-ACCESS read-only 
		STATUS current
		DESCRIPTION  "stream 0d frame receive" 
		::={ acosSlbQuicS 56 } 

		stream0dFrameTx OBJECT-TYPE
		SYNTAX  CounterBasedGauge64 
		MAX-ACCESS read-only 
		STATUS current
		DESCRIPTION  "stream 0d frame send" 
		::={ acosSlbQuicS 57 } 

		stream0eFrameRx OBJECT-TYPE
		SYNTAX  CounterBasedGauge64 
		MAX-ACCESS read-only 
		STATUS current
		DESCRIPTION  "stream 0e frame receive" 
		::={ acosSlbQuicS 58 } 

		stream0eFrameTx OBJECT-TYPE
		SYNTAX  CounterBasedGauge64 
		MAX-ACCESS read-only 
		STATUS current
		DESCRIPTION  "stream 0e frame send" 
		::={ acosSlbQuicS 59 } 

		stream0fFrameRx OBJECT-TYPE
		SYNTAX  CounterBasedGauge64 
		MAX-ACCESS read-only 
		STATUS current
		DESCRIPTION  "stream 0f frame receive" 
		::={ acosSlbQuicS 60 } 

		stream0fFrameTx OBJECT-TYPE
		SYNTAX  CounterBasedGauge64 
		MAX-ACCESS read-only 
		STATUS current
		DESCRIPTION  "stream 0f frame send" 
		::={ acosSlbQuicS 61 } 

		maxDataFrameRx OBJECT-TYPE
		SYNTAX  CounterBasedGauge64 
		MAX-ACCESS read-only 
		STATUS current
		DESCRIPTION  "max data frame receive" 
		::={ acosSlbQuicS 62 } 

		maxDataFrameTx OBJECT-TYPE
		SYNTAX  CounterBasedGauge64 
		MAX-ACCESS read-only 
		STATUS current
		DESCRIPTION  "max data frame send" 
		::={ acosSlbQuicS 63 } 

		maxStreamDataFrameRx OBJECT-TYPE
		SYNTAX  CounterBasedGauge64 
		MAX-ACCESS read-only 
		STATUS current
		DESCRIPTION  "max stream data frame receive" 
		::={ acosSlbQuicS 64 } 

		maxStreamDataFrameTx OBJECT-TYPE
		SYNTAX  CounterBasedGauge64 
		MAX-ACCESS read-only 
		STATUS current
		DESCRIPTION  "max stream data frame send" 
		::={ acosSlbQuicS 65 } 

		maxBiStreamFrameRx OBJECT-TYPE
		SYNTAX  CounterBasedGauge64 
		MAX-ACCESS read-only 
		STATUS current
		DESCRIPTION  "max bi stream frame receive" 
		::={ acosSlbQuicS 66 } 

		maxBiStreamFrameTx OBJECT-TYPE
		SYNTAX  CounterBasedGauge64 
		MAX-ACCESS read-only 
		STATUS current
		DESCRIPTION  "max bi stream frame send" 
		::={ acosSlbQuicS 67 } 

		maxUniStreamFrameRx OBJECT-TYPE
		SYNTAX  CounterBasedGauge64 
		MAX-ACCESS read-only 
		STATUS current
		DESCRIPTION  "max uni stream frame receive" 
		::={ acosSlbQuicS 68 } 

		maxUniStreamFrameTx OBJECT-TYPE
		SYNTAX  CounterBasedGauge64 
		MAX-ACCESS read-only 
		STATUS current
		DESCRIPTION  "max uni stream frame send" 
		::={ acosSlbQuicS 69 } 

		dataBlockedFrameRx OBJECT-TYPE
		SYNTAX  CounterBasedGauge64 
		MAX-ACCESS read-only 
		STATUS current
		DESCRIPTION  "data blocked frame receive" 
		::={ acosSlbQuicS 70 } 

		dataBlockedFrameTx OBJECT-TYPE
		SYNTAX  CounterBasedGauge64 
		MAX-ACCESS read-only 
		STATUS current
		DESCRIPTION  "data blocked frame send" 
		::={ acosSlbQuicS 71 } 

		streamDataBlockedFrameRx OBJECT-TYPE
		SYNTAX  CounterBasedGauge64 
		MAX-ACCESS read-only 
		STATUS current
		DESCRIPTION  "stream data blocked frame receive" 
		::={ acosSlbQuicS 72 } 

		streamDataBlockedFrameTx OBJECT-TYPE
		SYNTAX  CounterBasedGauge64 
		MAX-ACCESS read-only 
		STATUS current
		DESCRIPTION  "stream data blocked frame send" 
		::={ acosSlbQuicS 73 } 

		biStreamDataBlockedFrameRx OBJECT-TYPE
		SYNTAX  CounterBasedGauge64 
		MAX-ACCESS read-only 
		STATUS current
		DESCRIPTION  "bi stream data blocked frame receive" 
		::={ acosSlbQuicS 74 } 

		biStreamDataBlockedFrameTx OBJECT-TYPE
		SYNTAX  CounterBasedGauge64 
		MAX-ACCESS read-only 
		STATUS current
		DESCRIPTION  "bi stream data blocked frame send" 
		::={ acosSlbQuicS 75 } 

		uniStreamDataBlockedFrameRx OBJECT-TYPE
		SYNTAX  CounterBasedGauge64 
		MAX-ACCESS read-only 
		STATUS current
		DESCRIPTION  "uni stream data blocked frame receive" 
		::={ acosSlbQuicS 76 } 

		uniStreamDataBlockedFrameTx OBJECT-TYPE
		SYNTAX  CounterBasedGauge64 
		MAX-ACCESS read-only 
		STATUS current
		DESCRIPTION  "uni stream data blocked frame send" 
		::={ acosSlbQuicS 77 } 

		newConnIdFrameRx OBJECT-TYPE
		SYNTAX  CounterBasedGauge64 
		MAX-ACCESS read-only 
		STATUS current
		DESCRIPTION  "new conn id frame receive" 
		::={ acosSlbQuicS 78 } 

		newConnIdFrameTx OBJECT-TYPE
		SYNTAX  CounterBasedGauge64 
		MAX-ACCESS read-only 
		STATUS current
		DESCRIPTION  "new conn id frame send" 
		::={ acosSlbQuicS 79 } 

		retireConnIdFrameRx OBJECT-TYPE
		SYNTAX  CounterBasedGauge64 
		MAX-ACCESS read-only 
		STATUS current
		DESCRIPTION  "retire conn id frame receive" 
		::={ acosSlbQuicS 80 } 

		retireConnIdFrameTx OBJECT-TYPE
		SYNTAX  CounterBasedGauge64 
		MAX-ACCESS read-only 
		STATUS current
		DESCRIPTION  "retire conn id frame send" 
		::={ acosSlbQuicS 81 } 

		pathChallengeFrameRx OBJECT-TYPE
		SYNTAX  CounterBasedGauge64 
		MAX-ACCESS read-only 
		STATUS current
		DESCRIPTION  "path challenge frame receive" 
		::={ acosSlbQuicS 82 } 

		pathChallengeFrameTx OBJECT-TYPE
		SYNTAX  CounterBasedGauge64 
		MAX-ACCESS read-only 
		STATUS current
		DESCRIPTION  "path challenge frame send" 
		::={ acosSlbQuicS 83 } 

		pathResponseFrameRx OBJECT-TYPE
		SYNTAX  CounterBasedGauge64 
		MAX-ACCESS read-only 
		STATUS current
		DESCRIPTION  "path response frame receive" 
		::={ acosSlbQuicS 84 } 

		pathResponseFrameTx OBJECT-TYPE
		SYNTAX  CounterBasedGauge64 
		MAX-ACCESS read-only 
		STATUS current
		DESCRIPTION  "path response frame send" 
		::={ acosSlbQuicS 85 } 

		connCloseFrameRx OBJECT-TYPE
		SYNTAX  CounterBasedGauge64 
		MAX-ACCESS read-only 
		STATUS current
		DESCRIPTION  "conn close frame receive" 
		::={ acosSlbQuicS 86 } 

		connCloseFrameTx OBJECT-TYPE
		SYNTAX  CounterBasedGauge64 
		MAX-ACCESS read-only 
		STATUS current
		DESCRIPTION  "conn close frame send" 
		::={ acosSlbQuicS 87 } 

		appConnCloseFrameRx OBJECT-TYPE
		SYNTAX  CounterBasedGauge64 
		MAX-ACCESS read-only 
		STATUS current
		DESCRIPTION  "app conn close frame receive" 
		::={ acosSlbQuicS 88 } 

		appConnCloseFrameTx OBJECT-TYPE
		SYNTAX  CounterBasedGauge64 
		MAX-ACCESS read-only 
		STATUS current
		DESCRIPTION  "app conn close frame send" 
		::={ acosSlbQuicS 89 } 

		handshakeDoneFrameRx OBJECT-TYPE
		SYNTAX  CounterBasedGauge64 
		MAX-ACCESS read-only 
		STATUS current
		DESCRIPTION  "handshake done frame receive" 
		::={ acosSlbQuicS 90 } 

		handshakeDoneFrameTx OBJECT-TYPE
		SYNTAX  CounterBasedGauge64 
		MAX-ACCESS read-only 
		STATUS current
		DESCRIPTION  "handshake done frame send" 
		::={ acosSlbQuicS 91 } 

		unknownFrame OBJECT-TYPE
		SYNTAX  CounterBasedGauge64 
		MAX-ACCESS read-only 
		STATUS current
		DESCRIPTION  "Unknown frame" 
		::={ acosSlbQuicS 92 } 

		streamFinReceive OBJECT-TYPE
		SYNTAX  CounterBasedGauge64 
		MAX-ACCESS read-only 
		STATUS current
		DESCRIPTION  "Stream FIN receive" 
		::={ acosSlbQuicS 93 } 

		streamFinUp OBJECT-TYPE
		SYNTAX  CounterBasedGauge64 
		MAX-ACCESS read-only 
		STATUS current
		DESCRIPTION  "Stream FIN up" 
		::={ acosSlbQuicS 138 } 

		streamFinDown OBJECT-TYPE
		SYNTAX  CounterBasedGauge64 
		MAX-ACCESS read-only 
		STATUS current
		DESCRIPTION  "Stream FIN down" 
		::={ acosSlbQuicS 139 } 

		streamFinSend OBJECT-TYPE
		SYNTAX  CounterBasedGauge64 
		MAX-ACCESS read-only 
		STATUS current
		DESCRIPTION  "Stream FIN send" 
		::={ acosSlbQuicS 94 } 

		streamCongest OBJECT-TYPE
		SYNTAX  CounterBasedGauge64 
		MAX-ACCESS read-only 
		STATUS current
		DESCRIPTION  "Stream congest" 
		::={ acosSlbQuicS 95 } 

		streamOpen OBJECT-TYPE
		SYNTAX  CounterBasedGauge64 
		MAX-ACCESS read-only 
		STATUS current
		DESCRIPTION  "Stream open" 
		::={ acosSlbQuicS 96 } 

		streamPauseData OBJECT-TYPE
		SYNTAX  CounterBasedGauge64 
		MAX-ACCESS read-only 
		STATUS current
		DESCRIPTION  "Stream pause data" 
		::={ acosSlbQuicS 97 } 

		streamResumeData OBJECT-TYPE
		SYNTAX  CounterBasedGauge64 
		MAX-ACCESS read-only 
		STATUS current
		DESCRIPTION  "Stream resume data" 
		::={ acosSlbQuicS 98 } 

		streamNotSend OBJECT-TYPE
		SYNTAX  CounterBasedGauge64 
		MAX-ACCESS read-only 
		STATUS current
		DESCRIPTION  "Stream not send" 
		::={ acosSlbQuicS 99 } 

		streamStopSend OBJECT-TYPE
		SYNTAX  CounterBasedGauge64 
		MAX-ACCESS read-only 
		STATUS current
		DESCRIPTION  "Stream stop send" 
		::={ acosSlbQuicS 231 } 

		streamCreated OBJECT-TYPE
		SYNTAX  CounterBasedGauge64 
		MAX-ACCESS read-only 
		STATUS current
		DESCRIPTION  "Stream created" 
		::={ acosSlbQuicS 172 } 

		streamFreed OBJECT-TYPE
		SYNTAX  CounterBasedGauge64 
		MAX-ACCESS read-only 
		STATUS current
		DESCRIPTION  "Stream freed" 
		::={ acosSlbQuicS 173 } 

		iNITIALRx OBJECT-TYPE
		SYNTAX  CounterBasedGauge64 
		MAX-ACCESS read-only 
		STATUS current
		DESCRIPTION  "INITIAL receive" 
		::={ acosSlbQuicS 100 } 

		iNITIALTx OBJECT-TYPE
		SYNTAX  CounterBasedGauge64 
		MAX-ACCESS read-only 
		STATUS current
		DESCRIPTION  "INITIAL send" 
		::={ acosSlbQuicS 101 } 

		rTT0Rx OBJECT-TYPE
		SYNTAX  CounterBasedGauge64 
		MAX-ACCESS read-only 
		STATUS current
		DESCRIPTION  "RTT_0 receive" 
		::={ acosSlbQuicS 102 } 

		rTT0Tx OBJECT-TYPE
		SYNTAX  CounterBasedGauge64 
		MAX-ACCESS read-only 
		STATUS current
		DESCRIPTION  "RTT_0 send" 
		::={ acosSlbQuicS 103 } 

		hANDSHAKERx OBJECT-TYPE
		SYNTAX  CounterBasedGauge64 
		MAX-ACCESS read-only 
		STATUS current
		DESCRIPTION  "HANDSHAKE receive" 
		::={ acosSlbQuicS 104 } 

		hANDSHAKETx OBJECT-TYPE
		SYNTAX  CounterBasedGauge64 
		MAX-ACCESS read-only 
		STATUS current
		DESCRIPTION  "HANDSHAKE send" 
		::={ acosSlbQuicS 105 } 

		rETRYRx OBJECT-TYPE
		SYNTAX  CounterBasedGauge64 
		MAX-ACCESS read-only 
		STATUS current
		DESCRIPTION  "RETRY receive" 
		::={ acosSlbQuicS 106 } 

		rETRYTx OBJECT-TYPE
		SYNTAX  CounterBasedGauge64 
		MAX-ACCESS read-only 
		STATUS current
		DESCRIPTION  "RETRY send" 
		::={ acosSlbQuicS 107 } 

		vERRx OBJECT-TYPE
		SYNTAX  CounterBasedGauge64 
		MAX-ACCESS read-only 
		STATUS current
		DESCRIPTION  "Version receive" 
		::={ acosSlbQuicS 108 } 

		vERTx OBJECT-TYPE
		SYNTAX  CounterBasedGauge64 
		MAX-ACCESS read-only 
		STATUS current
		DESCRIPTION  "Version send" 
		::={ acosSlbQuicS 109 } 

		rTTUpdated OBJECT-TYPE
		SYNTAX  CounterBasedGauge64 
		MAX-ACCESS read-only 
		STATUS current
		DESCRIPTION  "RTT updated" 
		::={ acosSlbQuicS 110 } 

		needsAck OBJECT-TYPE
		SYNTAX  CounterBasedGauge64 
		MAX-ACCESS read-only 
		STATUS current
		DESCRIPTION  "Needs ACK" 
		::={ acosSlbQuicS 111 } 

		delayedAck OBJECT-TYPE
		SYNTAX  CounterBasedGauge64 
		MAX-ACCESS read-only 
		STATUS current
		DESCRIPTION  "Delayed ACK" 
		::={ acosSlbQuicS 112 } 

		packetRx OBJECT-TYPE
		SYNTAX  CounterBasedGauge64 
		MAX-ACCESS read-only 
		STATUS current
		DESCRIPTION  "Packet receive" 
		::={ acosSlbQuicS 113 } 

		packetTx OBJECT-TYPE
		SYNTAX  CounterBasedGauge64 
		MAX-ACCESS read-only 
		STATUS current
		DESCRIPTION  "Packet send" 
		::={ acosSlbQuicS 114 } 

		packetTxFailed OBJECT-TYPE
		SYNTAX  CounterBasedGauge64 
		MAX-ACCESS read-only 
		STATUS current
		DESCRIPTION  "Packet send failed" 
		::={ acosSlbQuicS 115 } 

		congestWndInc OBJECT-TYPE
		SYNTAX  CounterBasedGauge64 
		MAX-ACCESS read-only 
		STATUS current
		DESCRIPTION  "Congestion window increase" 
		::={ acosSlbQuicS 116 } 

		congestWndDec OBJECT-TYPE
		SYNTAX  CounterBasedGauge64 
		MAX-ACCESS read-only 
		STATUS current
		DESCRIPTION  "Congestion window decrease" 
		::={ acosSlbQuicS 117 } 

		noCongestWnd OBJECT-TYPE
		SYNTAX  CounterBasedGauge64 
		MAX-ACCESS read-only 
		STATUS current
		DESCRIPTION  "No congestion window" 
		::={ acosSlbQuicS 118 } 

		burstLimited OBJECT-TYPE
		SYNTAX  CounterBasedGauge64 
		MAX-ACCESS read-only 
		STATUS current
		DESCRIPTION  "Burst limited" 
		::={ acosSlbQuicS 119 } 

		packetLoopLimited OBJECT-TYPE
		SYNTAX  CounterBasedGauge64 
		MAX-ACCESS read-only 
		STATUS current
		DESCRIPTION  "Packet loop limited" 
		::={ acosSlbQuicS 137 } 

		receiveWndLimited OBJECT-TYPE
		SYNTAX  CounterBasedGauge64 
		MAX-ACCESS read-only 
		STATUS current
		DESCRIPTION  "Receive window limited" 
		::={ acosSlbQuicS 144 } 

		parseError OBJECT-TYPE
		SYNTAX  CounterBasedGauge64 
		MAX-ACCESS read-only 
		STATUS current
		DESCRIPTION  "Parse error" 
		::={ acosSlbQuicS 120 } 

		errorClose OBJECT-TYPE
		SYNTAX  CounterBasedGauge64 
		MAX-ACCESS read-only 
		STATUS current
		DESCRIPTION  "Conn closed of error" 
		::={ acosSlbQuicS 121 } 

		unknownScid OBJECT-TYPE
		SYNTAX  CounterBasedGauge64 
		MAX-ACCESS read-only 
		STATUS current
		DESCRIPTION  "Unknown scid" 
		::={ acosSlbQuicS 122 } 

		dcidMismatch OBJECT-TYPE
		SYNTAX  CounterBasedGauge64 
		MAX-ACCESS read-only 
		STATUS current
		DESCRIPTION  "Dcid mismatch" 
		::={ acosSlbQuicS 123 } 

		packetTooShort OBJECT-TYPE
		SYNTAX  CounterBasedGauge64 
		MAX-ACCESS read-only 
		STATUS current
		DESCRIPTION  "Packet_too_short" 
		::={ acosSlbQuicS 124 } 

		invalidVersion OBJECT-TYPE
		SYNTAX  CounterBasedGauge64 
		MAX-ACCESS read-only 
		STATUS current
		DESCRIPTION  "Invalid version" 
		::={ acosSlbQuicS 125 } 

		invalidPacket OBJECT-TYPE
		SYNTAX  CounterBasedGauge64 
		MAX-ACCESS read-only 
		STATUS current
		DESCRIPTION  "Invalid packet" 
		::={ acosSlbQuicS 126 } 

		invalidConnMatch OBJECT-TYPE
		SYNTAX  CounterBasedGauge64 
		MAX-ACCESS read-only 
		STATUS current
		DESCRIPTION  "Invalid conn match" 
		::={ acosSlbQuicS 145 } 

		invalidSessionPacket OBJECT-TYPE
		SYNTAX  CounterBasedGauge64 
		MAX-ACCESS read-only 
		STATUS current
		DESCRIPTION  "Invalid session packet" 
		::={ acosSlbQuicS 149 } 

		statelessReset OBJECT-TYPE
		SYNTAX  CounterBasedGauge64 
		MAX-ACCESS read-only 
		STATUS current
		DESCRIPTION  "Stateless resert" 
		::={ acosSlbQuicS 127 } 

		packetLost OBJECT-TYPE
		SYNTAX  CounterBasedGauge64 
		MAX-ACCESS read-only 
		STATUS current
		DESCRIPTION  "Packet lost" 
		::={ acosSlbQuicS 128 } 

		packetDrop OBJECT-TYPE
		SYNTAX  CounterBasedGauge64 
		MAX-ACCESS read-only 
		STATUS current
		DESCRIPTION  "Packet drop" 
		::={ acosSlbQuicS 129 } 

		packetRetransmit OBJECT-TYPE
		SYNTAX  CounterBasedGauge64 
		MAX-ACCESS read-only 
		STATUS current
		DESCRIPTION  "Packet retransmit" 
		::={ acosSlbQuicS 130 } 

		packetOutOfOrder OBJECT-TYPE
		SYNTAX  CounterBasedGauge64 
		MAX-ACCESS read-only 
		STATUS current
		DESCRIPTION  "Packet out of order" 
		::={ acosSlbQuicS 131 } 

		quicPacketDrop OBJECT-TYPE
		SYNTAX  CounterBasedGauge64 
		MAX-ACCESS read-only 
		STATUS current
		DESCRIPTION  "Quic packet drop" 
		::={ acosSlbQuicS 170 } 

		encodeError OBJECT-TYPE
		SYNTAX  CounterBasedGauge64 
		MAX-ACCESS read-only 
		STATUS current
		DESCRIPTION  "Encode error" 
		::={ acosSlbQuicS 171 } 

		decodeFailed OBJECT-TYPE
		SYNTAX  CounterBasedGauge64 
		MAX-ACCESS read-only 
		STATUS current
		DESCRIPTION  "Decode failed" 
		::={ acosSlbQuicS 176 } 

		decodeStreamError OBJECT-TYPE
		SYNTAX  CounterBasedGauge64 
		MAX-ACCESS read-only 
		STATUS current
		DESCRIPTION  "Decode stream error" 
		::={ acosSlbQuicS 177 } 

		exceedFlowControl OBJECT-TYPE
		SYNTAX  CounterBasedGauge64 
		MAX-ACCESS read-only 
		STATUS current
		DESCRIPTION  "Exceed flow control" 
		::={ acosSlbQuicS 181 } 

		cryptoStreamNotFound OBJECT-TYPE
		SYNTAX  CounterBasedGauge64 
		MAX-ACCESS read-only 
		STATUS current
		DESCRIPTION  "Crypto stream not found" 
		::={ acosSlbQuicS 185 } 

		exceedMaxStreamId OBJECT-TYPE
		SYNTAX  CounterBasedGauge64 
		MAX-ACCESS read-only 
		STATUS current
		DESCRIPTION  "Exceed_max_stream_id" 
		::={ acosSlbQuicS 187 } 

		streamIdMismatch OBJECT-TYPE
		SYNTAX  CounterBasedGauge64 
		MAX-ACCESS read-only 
		STATUS current
		DESCRIPTION  "Stream_id_mismatch" 
		::={ acosSlbQuicS 188 } 

		ackDelayHuge OBJECT-TYPE
		SYNTAX  CounterBasedGauge64 
		MAX-ACCESS read-only 
		STATUS current
		DESCRIPTION  "Ack_delay_huge" 
		::={ acosSlbQuicS 189 } 

		ackRngHuge1 OBJECT-TYPE
		SYNTAX  CounterBasedGauge64 
		MAX-ACCESS read-only 
		STATUS current
		DESCRIPTION  "Ack_rng_huge_1" 
		::={ acosSlbQuicS 190 } 

		ackRngHuge2 OBJECT-TYPE
		SYNTAX  CounterBasedGauge64 
		MAX-ACCESS read-only 
		STATUS current
		DESCRIPTION  "Ack_rng_huge_2" 
		::={ acosSlbQuicS 191 } 

		ackRngHuge3 OBJECT-TYPE
		SYNTAX  CounterBasedGauge64 
		MAX-ACCESS read-only 
		STATUS current
		DESCRIPTION  "Ack_rng_huge_3" 
		::={ acosSlbQuicS 193 } 

		tooNoisyFuzzing OBJECT-TYPE
		SYNTAX  CounterBasedGauge64 
		MAX-ACCESS read-only 
		STATUS current
		DESCRIPTION  "Too_noisy_fuzzing" 
		::={ acosSlbQuicS 192 } 

		maxStreamTooBig OBJECT-TYPE
		SYNTAX  CounterBasedGauge64 
		MAX-ACCESS read-only 
		STATUS current
		DESCRIPTION  "Max_stream_too_big" 
		::={ acosSlbQuicS 195 } 

		streamBlocked OBJECT-TYPE
		SYNTAX  CounterBasedGauge64 
		MAX-ACCESS read-only 
		STATUS current
		DESCRIPTION  "Stream_blocked" 
		::={ acosSlbQuicS 196 } 

		newConnIdLenZero OBJECT-TYPE
		SYNTAX  CounterBasedGauge64 
		MAX-ACCESS read-only 
		STATUS current
		DESCRIPTION  "New_conn_id_len_zero" 
		::={ acosSlbQuicS 197 } 

		newConnIdLenNonZero OBJECT-TYPE
		SYNTAX  CounterBasedGauge64 
		MAX-ACCESS read-only 
		STATUS current
		DESCRIPTION  "New_conn_id_len_non_zero" 
		::={ acosSlbQuicS 198 } 

		illegalStreamLen OBJECT-TYPE
		SYNTAX  CounterBasedGauge64 
		MAX-ACCESS read-only 
		STATUS current
		DESCRIPTION  "Illegal_stream_len" 
		::={ acosSlbQuicS 186 } 

		illegalReasonLen OBJECT-TYPE
		SYNTAX  CounterBasedGauge64 
		MAX-ACCESS read-only 
		STATUS current
		DESCRIPTION  "Illegal_reason_len" 
		::={ acosSlbQuicS 194 } 

		illegalSeq OBJECT-TYPE
		SYNTAX  CounterBasedGauge64 
		MAX-ACCESS read-only 
		STATUS current
		DESCRIPTION  "Illegal_seq" 
		::={ acosSlbQuicS 199 } 

		illegalRpt OBJECT-TYPE
		SYNTAX  CounterBasedGauge64 
		MAX-ACCESS read-only 
		STATUS current
		DESCRIPTION  "Illegal_rpt" 
		::={ acosSlbQuicS 200 } 

		illegalLen OBJECT-TYPE
		SYNTAX  CounterBasedGauge64 
		MAX-ACCESS read-only 
		STATUS current
		DESCRIPTION  "Illegal_len" 
		::={ acosSlbQuicS 201 } 

		illegalTokenLen OBJECT-TYPE
		SYNTAX  CounterBasedGauge64 
		MAX-ACCESS read-only 
		STATUS current
		DESCRIPTION  "Illegal_token_len" 
		::={ acosSlbQuicS 208 } 

		cannotInsertCid OBJECT-TYPE
		SYNTAX  CounterBasedGauge64 
		MAX-ACCESS read-only 
		STATUS current
		DESCRIPTION  "Cannot_insert_cid" 
		::={ acosSlbQuicS 202 } 

		cannotInsertSrt OBJECT-TYPE
		SYNTAX  CounterBasedGauge64 
		MAX-ACCESS read-only 
		STATUS current
		DESCRIPTION  "Cannot_insert_srt" 
		::={ acosSlbQuicS 203 } 

		cannotRetireCid OBJECT-TYPE
		SYNTAX  CounterBasedGauge64 
		MAX-ACCESS read-only 
		STATUS current
		DESCRIPTION  "Cannot_retire_cid" 
		::={ acosSlbQuicS 204 } 

		noNextScid OBJECT-TYPE
		SYNTAX  CounterBasedGauge64 
		MAX-ACCESS read-only 
		STATUS current
		DESCRIPTION  "No_next_scid" 
		::={ acosSlbQuicS 205 } 

		tokenLenTooLong OBJECT-TYPE
		SYNTAX  CounterBasedGauge64 
		MAX-ACCESS read-only 
		STATUS current
		DESCRIPTION  "Token_len_too_long" 
		::={ acosSlbQuicS 206 } 

		serverReceiveNewToken OBJECT-TYPE
		SYNTAX  CounterBasedGauge64 
		MAX-ACCESS read-only 
		STATUS current
		DESCRIPTION  "Server_receive_new_token" 
		::={ acosSlbQuicS 207 } 

		zeroFramePacket OBJECT-TYPE
		SYNTAX  CounterBasedGauge64 
		MAX-ACCESS read-only 
		STATUS current
		DESCRIPTION  "Zero_frame_packet" 
		::={ acosSlbQuicS 209 } 

		errFrameDec1 OBJECT-TYPE
		SYNTAX  CounterBasedGauge64 
		MAX-ACCESS read-only 
		STATUS current
		DESCRIPTION  "Err_frame_dec1" 
		::={ acosSlbQuicS 210 } 

		errFrameDec OBJECT-TYPE
		SYNTAX  CounterBasedGauge64 
		MAX-ACCESS read-only 
		STATUS current
		DESCRIPTION  "Err_frame_dec" 
		::={ acosSlbQuicS 211 } 

		errFrameDecb OBJECT-TYPE
		SYNTAX  CounterBasedGauge64 
		MAX-ACCESS read-only 
		STATUS current
		DESCRIPTION  "Err_frame_decb" 
		::={ acosSlbQuicS 212 } 

		errFrameFinalSize OBJECT-TYPE
		SYNTAX  CounterBasedGauge64 
		MAX-ACCESS read-only 
		STATUS current
		DESCRIPTION  "Err_frame_final_size" 
		::={ acosSlbQuicS 213 } 

		errFlowControl OBJECT-TYPE
		SYNTAX  CounterBasedGauge64 
		MAX-ACCESS read-only 
		STATUS current
		DESCRIPTION  "Err_flow_control" 
		::={ acosSlbQuicS 214 } 

		errProtocolViolation OBJECT-TYPE
		SYNTAX  CounterBasedGauge64 
		MAX-ACCESS read-only 
		STATUS current
		DESCRIPTION  "Err_protocol_violation" 
		::={ acosSlbQuicS 215 } 

		serverRxHandshakeDone OBJECT-TYPE
		SYNTAX  CounterBasedGauge64 
		MAX-ACCESS read-only 
		STATUS current
		DESCRIPTION  "Server_rx_handshake_done" 
		::={ acosSlbQuicS 216 } 

		pktAckedFailed OBJECT-TYPE
		SYNTAX  CounterBasedGauge64 
		MAX-ACCESS read-only 
		STATUS current
		DESCRIPTION  "Pkt_acked_failed" 
		::={ acosSlbQuicS 217 } 

		pnInsertFailed OBJECT-TYPE
		SYNTAX  CounterBasedGauge64 
		MAX-ACCESS read-only 
		STATUS current
		DESCRIPTION  "Pn insert failed" 
		::={ acosSlbQuicS 218 } 

		pnDeleteFailed OBJECT-TYPE
		SYNTAX  CounterBasedGauge64 
		MAX-ACCESS read-only 
		STATUS current
		DESCRIPTION  "Pn delete failed" 
		::={ acosSlbQuicS 219 } 

		ackedPacketFreed OBJECT-TYPE
		SYNTAX  CounterBasedGauge64 
		MAX-ACCESS read-only 
		STATUS current
		DESCRIPTION  "Acked packet freed" 
		::={ acosSlbQuicS 225 } 

		txBufferEnq OBJECT-TYPE
		SYNTAX  CounterBasedGauge64 
		MAX-ACCESS read-only 
		STATUS current
		DESCRIPTION  "Tx buffer enqueued" 
		::={ acosSlbQuicS 132 } 

		txBufferDeq OBJECT-TYPE
		SYNTAX  CounterBasedGauge64 
		MAX-ACCESS read-only 
		STATUS current
		DESCRIPTION  "Tx buffer dequeued" 
		::={ acosSlbQuicS 133 } 

		appBufferEnq OBJECT-TYPE
		SYNTAX  CounterBasedGauge64 
		MAX-ACCESS read-only 
		STATUS current
		DESCRIPTION  "App buffer enqueued" 
		::={ acosSlbQuicS 134 } 

		appBufferDeq OBJECT-TYPE
		SYNTAX  CounterBasedGauge64 
		MAX-ACCESS read-only 
		STATUS current
		DESCRIPTION  "App buffer dequeued" 
		::={ acosSlbQuicS 135 } 

		appBufferQueueFull OBJECT-TYPE
		SYNTAX  CounterBasedGauge64 
		MAX-ACCESS read-only 
		STATUS current
		DESCRIPTION  "App buffer queue full" 
		::={ acosSlbQuicS 136 } 

		iovBufferBind OBJECT-TYPE
		SYNTAX  CounterBasedGauge64 
		MAX-ACCESS read-only 
		STATUS current
		DESCRIPTION  "Iov buffer bind" 
		::={ acosSlbQuicS 166 } 

		iovBufferUnbind OBJECT-TYPE
		SYNTAX  CounterBasedGauge64 
		MAX-ACCESS read-only 
		STATUS current
		DESCRIPTION  "Iov buffer unbind" 
		::={ acosSlbQuicS 167 } 

		iovBufferDup OBJECT-TYPE
		SYNTAX  CounterBasedGauge64 
		MAX-ACCESS read-only 
		STATUS current
		DESCRIPTION  "Iov buffer dup" 
		::={ acosSlbQuicS 174 } 

		iovAllocLen OBJECT-TYPE
		SYNTAX  CounterBasedGauge64 
		MAX-ACCESS read-only 
		STATUS current
		DESCRIPTION  "Iov alloc len" 
		::={ acosSlbQuicS 175 } 

		iovIO OBJECT-TYPE
		SYNTAX  CounterBasedGauge64 
		MAX-ACCESS read-only 
		STATUS current
		DESCRIPTION  "Iov IO" 
		::={ acosSlbQuicS 223 } 

		iovSystem OBJECT-TYPE
		SYNTAX  CounterBasedGauge64 
		MAX-ACCESS read-only 
		STATUS current
		DESCRIPTION  "Iov System" 
		::={ acosSlbQuicS 224 } 

		noTxQueue OBJECT-TYPE
		SYNTAX  CounterBasedGauge64 
		MAX-ACCESS read-only 
		STATUS current
		DESCRIPTION  "No tx queue" 
		::={ acosSlbQuicS 178 } 

		wsocketCreated OBJECT-TYPE
		SYNTAX  CounterBasedGauge64 
		MAX-ACCESS read-only 
		STATUS current
		DESCRIPTION  "wsocket created" 
		::={ acosSlbQuicS 140 } 

		wsocketClosed OBJECT-TYPE
		SYNTAX  CounterBasedGauge64 
		MAX-ACCESS read-only 
		STATUS current
		DESCRIPTION  "wsocket closed" 
		::={ acosSlbQuicS 141 } 

		a10SocketCreated OBJECT-TYPE
		SYNTAX  CounterBasedGauge64 
		MAX-ACCESS read-only 
		STATUS current
		DESCRIPTION  "a10 socket created" 
		::={ acosSlbQuicS 142 } 

		a10SocketClosed OBJECT-TYPE
		SYNTAX  CounterBasedGauge64 
		MAX-ACCESS read-only 
		STATUS current
		DESCRIPTION  "a10 socket closed" 
		::={ acosSlbQuicS 143 } 

		noA10Socket OBJECT-TYPE
		SYNTAX  CounterBasedGauge64 
		MAX-ACCESS read-only 
		STATUS current
		DESCRIPTION  "no a10 socket" 
		::={ acosSlbQuicS 179 } 

		noOtherSideSocket OBJECT-TYPE
		SYNTAX  CounterBasedGauge64 
		MAX-ACCESS read-only 
		STATUS current
		DESCRIPTION  "no other side socket" 
		::={ acosSlbQuicS 180 } 

		noWEngine OBJECT-TYPE
		SYNTAX  CounterBasedGauge64 
		MAX-ACCESS read-only 
		STATUS current
		DESCRIPTION  "no w engine" 
		::={ acosSlbQuicS 184 } 

		noWSocket OBJECT-TYPE
		SYNTAX  CounterBasedGauge64 
		MAX-ACCESS read-only 
		STATUS current
		DESCRIPTION  "no w socket" 
		::={ acosSlbQuicS 220 } 

		onLdTimeout OBJECT-TYPE
		SYNTAX  CounterBasedGauge64 
		MAX-ACCESS read-only 
		STATUS current
		DESCRIPTION  "lost detection timeout" 
		::={ acosSlbQuicS 146 } 

		idleAlarm OBJECT-TYPE
		SYNTAX  CounterBasedGauge64 
		MAX-ACCESS read-only 
		STATUS current
		DESCRIPTION  "conn idle timeout" 
		::={ acosSlbQuicS 147 } 

		ackAlarm OBJECT-TYPE
		SYNTAX  CounterBasedGauge64 
		MAX-ACCESS read-only 
		STATUS current
		DESCRIPTION  "ack timeout" 
		::={ acosSlbQuicS 148 } 

		closeAlarm OBJECT-TYPE
		SYNTAX  CounterBasedGauge64 
		MAX-ACCESS read-only 
		STATUS current
		DESCRIPTION  "close timeout" 
		::={ acosSlbQuicS 221 } 

		delayAlarm OBJECT-TYPE
		SYNTAX  CounterBasedGauge64 
		MAX-ACCESS read-only 
		STATUS current
		DESCRIPTION  "delay timeout" 
		::={ acosSlbQuicS 222 } 

		quicMalloc OBJECT-TYPE
		SYNTAX  CounterBasedGauge64 
		MAX-ACCESS read-only 
		STATUS current
		DESCRIPTION  "QUIC malloc" 
		::={ acosSlbQuicS 150 } 

		quicFree OBJECT-TYPE
		SYNTAX  CounterBasedGauge64 
		MAX-ACCESS read-only 
		STATUS current
		DESCRIPTION  "QUIC free" 
		::={ acosSlbQuicS 151 } 

		quicMallocFailure OBJECT-TYPE
		SYNTAX  CounterBasedGauge64 
		MAX-ACCESS read-only 
		STATUS current
		DESCRIPTION  "QUIC malloc failure" 
		::={ acosSlbQuicS 152 } 

		quickMallocFailure OBJECT-TYPE
		SYNTAX  CounterBasedGauge64 
		MAX-ACCESS read-only 
		STATUS current
		DESCRIPTION  "quick malloc failure" 
		::={ acosSlbQuicS 153 } 

		quicLb OBJECT-TYPE
		SYNTAX  CounterBasedGauge64 
		MAX-ACCESS read-only 
		STATUS current
		DESCRIPTION  "QUIC LB" 
		::={ acosSlbQuicS 160 } 

		cidZero OBJECT-TYPE
		SYNTAX  CounterBasedGauge64 
		MAX-ACCESS read-only 
		STATUS current
		DESCRIPTION  "CID Zero" 
		::={ acosSlbQuicS 161 } 

		cidCpuHash OBJECT-TYPE
		SYNTAX  CounterBasedGauge64 
		MAX-ACCESS read-only 
		STATUS current
		DESCRIPTION  "CID CPU Hash" 
		::={ acosSlbQuicS 162 } 

		invalidCidSig OBJECT-TYPE
		SYNTAX  CounterBasedGauge64 
		MAX-ACCESS read-only 
		STATUS current
		DESCRIPTION  "Invalid CID Signature" 
		::={ acosSlbQuicS 163 } 

		keyUpdateRx OBJECT-TYPE
		SYNTAX  CounterBasedGauge64 
		MAX-ACCESS read-only 
		STATUS current
		DESCRIPTION  "QUIC TLS key update received" 
		::={ acosSlbQuicS 164 } 

		keyUpdateTx OBJECT-TYPE
		SYNTAX  CounterBasedGauge64 
		MAX-ACCESS read-only 
		STATUS current
		DESCRIPTION  "QUIC TLS key update sent" 
		::={ acosSlbQuicS 165 } 

END
