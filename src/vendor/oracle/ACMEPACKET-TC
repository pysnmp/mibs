--
--
-- ACMEPACKET-TC-MIB: Acme Packet Environmental Monitor MIB file
--
-- May 2012
--
-- Copyright (c) by Oracle Communications
-- All rights reserved.
----------------------------------------------------------------------

ACMEPACKET-TC DEFINITIONS ::= BEGIN

IMPORTS
        MODULE-IDENTITY
                FROM SNMPv2-SMI
        TEXTUAL-CONVENTION, DisplayString, TruthValue
                FROM SNMPv2-TC
        acmepacket
                FROM ACMEPACKET-SMI
        MODULE-COMPLIANCE, OBJECT-GROUP, NOTIFICATION-GROUP
                FROM SNMPv2-CONF;

apTextualConventions MODULE-IDENTITY
	LAST-UPDATED	"202203240000Z"
        ORGANIZATION 	"Oracle Communications"
        CONTACT-INFO
			"           	Customer Service
		 	Postal:		Oracle Communications
					100 Crosby Drive 
					Bedford, MA 01730
					US
		    	Tel:		1-800-633-0738
			Url:		www.oracle.com
		 	E-mail:		support@oracle.com"
        DESCRIPTION  "This module contains common textual convention
                     definitons used by various Acme Packet MIB modules."
        REVISION     "201202062305Z"
        DESCRIPTION  "Initial revision."
        REVISION     "201205052305Z"
        DESCRIPTION  "Expanded ApHardwareModuleFamily with niu10g."
	REVISION 	"201406260000Z" 			
        DESCRIPTION
	        "Updated Organization and Contact info."
        REVISION     "202007200000Z"
        DESCRIPTION  "Added ApDosThresholdTrafficType and
                          ApDosThresholdCrossState"
	REVISION "202010260000Z" 			
    	DESCRIPTION
			"Added ApCounterStatsType"
        REVISION "202012140000Z" 			
    	DESCRIPTION
			"Added serverUnreachable to ApStirStatsType"
        REVISION "202106070000Z" 			
    	DESCRIPTION
			"Added vsSuccessVerification to ApStirStatsType"
        REVISION "202202160000Z" 			
    	DESCRIPTION
			"Added apMSRPKPICounterStatsType"
        REVISION "202202160000Z" 			
    	DESCRIPTION
			"Added apMSRPKPIStatsType"
        REVISION "202203170000Z" 			
    	DESCRIPTION
			"Updated KPI names in ApMsrpKpiStatsType"
        REVISION "202203220000Z" 			
    	DESCRIPTION
			"Updated REPORTRate KPIs in ApMsrpKpiStatsType"
        REVISION "202203010000Z" 			
    	DESCRIPTION
			"Enhanced ApStirStatsType"
        REVISION "202203240000Z"
        DESCRIPTION
                        "Added ApNSEPRealmRvalueDNIndex and
                            ApNSEPRealmStatsType"
        REVISION "202205170000Z" 			
    	DESCRIPTION
			"Added asServiceUnreachable and
                vsServiceUnreachable to ApStirStatsType"

        ::= { acmepacket 0 }


ApHardwareModuleFamily ::= TEXTUAL-CONVENTION
        STATUS          current
        DESCRIPTION
               "The hardware module types."
        SYNTAX INTEGER {
	                unknown(0),
			spu(17),
			npu(18),
			tcu(19),
			niuCopper(24),
			niuFiber(25),
			miu(26),
			fanTray(240),
			powerSupply(241),
			niu10g(242)
		       }

ApRedundancyState ::= TEXTUAL-CONVENTION
        STATUS          current
        DESCRIPTION
               "The redundancy states that system or card can be in."
        SYNTAX INTEGER {
                unknown(0),             -- unrecognised state
                initial(1),             -- initial stage
                active(2),              -- active state
                standby(3),             -- standby state
                outOfService(4),        -- out of service
                unassigned(5),          -- unassigned state
                activePending(6),       -- becoming active
                standbyPending(7),      -- becoming standby
                outOfServicePending(8), -- becoming OOS
                recovery(9)             -- recovey state
                }


ApPhyPortType ::= TEXTUAL-CONVENTION
        STATUS          current
        DESCRIPTION
               "The physical port type."
        SYNTAX INTEGER {
	                unknown(0),
			sfp(1)
		       }

ApPresence ::= TEXTUAL-CONVENTION
        STATUS          current
        DESCRIPTION
               "The Presence of the physical entity."
        SYNTAX INTEGER {
	                unknown(0),
			inserted(1),
			removed(2)
		       }

ApTransportType ::= TEXTUAL-CONVENTION
        STATUS          current
        DESCRIPTION
               "The transport type."
        SYNTAX INTEGER {
	                unknown(0),
			tcp(1),
			sctp(2)
		       }

ApServerStatus ::= TEXTUAL-CONVENTION
        STATUS          current
        DESCRIPTION
               "The server status ."
        SYNTAX INTEGER { 	
	                inservice(0),
			lowerpriority(1),
			oosunreachable(2)
		       }

ApDiamResultCode ::= TEXTUAL-CONVENTION
       STATUS                current
       DESCRIPTION
              "The Result-Code AVP (268) value 
               RFC 3588, 7.1. Result-Code AVP"
       SYNTAX  INTEGER {
                    diameterMultiRoundAuth(1001),
                    diameterSuccess(2001),
                    diameterLimitedSuccess(2002),
                    diameterCommandUnsupported(3001),
                    diameterUnableToDeliver(3002),
                    diameterRealmNotServed(3003),
                    diameterTooBusy(3004),
                    diameterLoopDetected(3005),
                    diameterRedirectIndicatoion(3006),
                    diameterApplicationUnsupported(3007),
                    diameterInvalidHdrBits(3008),
                    diameterInvalidAvpBits(3009),
                    diameterUnknownPeer(3010),
                    diameterAuthenticationRejected(4001),
                    diameterOutOfSpace(4002),
                    electionLost(4003),
                    diameterAvpUnsupported(5001),
                    diameterUnknownSessionId(5002),
                    diameterAuthoriszationRejected(5003),
                    diameterInvalidAvpValue(5004),
                    diameterMissingAvp(5005),
                    diameterResourcesExceeded(5006),
                    diameterContradictingAvps(5007),
                    diameterAvpNotAllowed(5008),
                    diameterAvpTooManyTimes(5009),
                    diameterNoCommonApplication(5010),
                    diameterUnsupportedVersion(5011),
                    diameterUnableToComply(5012),
                    diameterInvalidBitInHeader(5013),
                    diameterInvalidAvpLength(5014),
                    diameterInvalidMessageLength(5015),
                    diameterInvalidAvpBitCombo(5016),
                    diameterNoCommonSecurity(5017)
               }
       
ApPercentage ::= TEXTUAL-CONVENTION
--	DISPLAY_HINT "d"
	STATUS		 current
	DESCRIPTION
		"This value is percentage. For example, if the value from 
		GETs is 15, which means 15%, or 0.15."
	SYNTAX         INTEGER (0..100)

ApSipMethod ::= TEXTUAL-CONVENTION
       STATUS                current
       DESCRIPTION
              "The SIP message method"
       SYNTAX  INTEGER {
                    other(1),
                    invite(2),
                    ack(3),
                    bye(4),
                    register(5),
                    cancel(6),
                    prack(7),
                    options(8),
                    info(9),
                    subscribe(10),
                    notify(11),
                    refer(12),
                    update(13),
                    message(14),
                    publish(15)
               }                             

ApThreadOverloaded ::= TEXTUAL-CONVENTION
       STATUS                current
       DESCRIPTION
              "Data type for thread overload"
       SYNTAX  INTEGER {
                    notApplicable(1),
                    true(2),
                    false(3)
               }

ApCommMonitorState ::= TEXTUAL-CONVENTION
       STATUS                current
       DESCRIPTION
              "The commMonitor state."
       SYNTAX INTEGER {    
                   outofservice (0),
            	   connecting(1),
                   connected (2),
            	   inservice(3)
               }
               
ApAclType ::= TEXTUAL-CONVENTION
        STATUS          current
        DESCRIPTION
               "The acl type."
        SYNTAX INTEGER {
                    untrusted(0),
                    trusted(1)
               }

ApDosThresholdTrafficType ::= TEXTUAL-CONVENTION
        STATUS  current
        DESCRIPTION
                "Type of traffic "
        SYNTAX  INTEGER {
                        trusted(1),
                        untrusted(2),
                        arp(3)
                        }

ApDosThresholdCrossState ::= TEXTUAL-CONVENTION
        STATUS  current
        DESCRIPTION
                "if threshold has crossed or not"
        SYNTAX  INTEGER {
                        not-crossed(0),
                        crossed(1)
                        }

ApCounterStatsType ::= TEXTUAL-CONVENTION
        STATUS  current
        DESCRIPTION
                "Type of counter stats "
        SYNTAX  INTEGER {
                        recent(1),
                        total(2),
                        permax(3)
                        }

ApStirStatsType ::= TEXTUAL-CONVENTION
        STATUS  current
        DESCRIPTION
                "Type of STIR stats "
        SYNTAX  INTEGER {
                asQueries(1),
                asSuccessResponses(2),
                asFailResponses(3),
                asFailServiceException(4),
                asFailPolicyException(5),
                vsQueries(6),
                vsSuccessResponses(7),
                vsFailResponses(8),
                vsSuccessVerification(9),
                vsFailVerification(10),
                vsFailServiceException(11),
                vsFailPolicyException(12),
                serverUnreachable(13),
                asSentInviteswithShakenPASSportA(14),
                asSentInviteswithShakenPASSportB(15),
                asSentInviteswithShakenPASSportC(16),
                asSentInviteswithdivPASSport(17),
                vsReceivedInviteswithNoPASSport(18),
                vsReceivedInviteswithShakenPASSport(19),
                vsReceivedInviteswithDivPASSport(20),
                vsSentInviteswithTNValidationPassed(21),
                vsSentInviteswithTNValidationFailed(22),
                vsSentInviteswithNoTNValidation(23),
                asServiceUnreachable(24),
                vsServiceUnreachable(25),
                apStirStatsTypeMax(26)
                        }
ApMsrpKpiStatsCounterType ::= TEXTUAL-CONVENTION
        STATUS  current
        DESCRIPTION
                "Type of counter stats "
        SYNTAX  INTEGER {
			recent(1),
                        high(2),
                        total(3),
			ltotal(4),
			lpermax(5),
			lhigh(6)
                        }

ApMsrpKpiStatsType ::= TEXTUAL-CONVENTION
        STATUS  current
        DESCRIPTION
                "Type of MSRP KPI stats "
        SYNTAX  INTEGER {
                        msrp-AvgSENDTransTx(1),
                        msrp-AvgChatSENDTransTx(2),
                        msrp-AvgIsTypingSENDTransTx(3),
                        msrp-AvgReceiptSENDTransTx(4),
                        msrp-AvgSENDMsgBytesTx(5),
                        msrp-AvgChatSENDMsgBytesTx(6),
                        msrp-AvgIsTypingSENDMsgBytesTx(7),
                        msrp-AvgReceiptSENDMsgBytesTx(8),
                        msrp-SENDMsgBytesTx(9),
                        msrp-ChatSENDMsgBytesTx(10),
                        msrp-IsTypingSENDMsgBytesTx(11),
                        msrp-ReceiptSENDMsgBytesTx(12),
                        msrp-SuccessREPORTTransTx(13),
                        msrp-FailureREPORTTransTx(14),
                        msrp-AvgSuccessREPORTMsgBytesTx(15),
                        msrp-AvgFailureREPORTMsgBytesTx(16),
                        msrp-AvgFailureREPORTRateTx(17),
                        msrp-AvgSuccessREPORTRateTx(18),
                        msrp-REPORTTrans400Tx(19),
                        msrp-REPORTTrans401Tx(20),
                        msrp-REPORTTrans403Tx(21),
                        msrp-REPORTTrans404Tx(22),
                        msrp-REPORTTrans408Tx(23),
                        msrp-REPORTTrans413Tx(24),
                        msrp-REPORTTrans415Tx(25),
                        msrp-REPORTTrans423Tx(26),
                        msrp-REPORTTrans424Tx(27),
                        msrp-REPORTTrans425Tx(28),
                        msrp-REPORTTrans428Tx(29),
                        msrp-REPORTTrans481Tx(30),
                        msrp-REPORTTrans501Tx(31),
                        msrp-REPORTTrans506Tx(32),
                        msrp-AvgFailureREPORTMsgBytes400Tx(33),
                        msrp-AvgFailureREPORTMsgBytes401Tx(34),
                        msrp-AvgFailureREPORTMsgBytes403Tx(35),
                        msrp-AvgFailureREPORTMsgBytes404Tx(36),
                        msrp-AvgFailureREPORTMsgBytes408Tx(37),
                        msrp-AvgFailureREPORTMsgBytes413Tx(38),
                        msrp-AvgFailureREPORTMsgBytes415Tx(39),
                        msrp-AvgFailureREPORTMsgBytes423Tx(40),
                        msrp-AvgFailureREPORTMsgBytes424Tx(41),
                        msrp-AvgFailureREPORTMsgBytes425Tx(42),
                        msrp-AvgFailureREPORTMsgBytes428Tx(43),
                        msrp-AvgFailureREPORTMsgBytes481Tx(44),
                        msrp-AvgFailureREPORTMsgBytes501Tx(45),
                        msrp-AvgFailureREPORTMsgBytes506Tx(46),
                        msrp-TransResponsesTx(47),
                        msrp-SuccessTransResponsesTx(48),
                        msrp-TransResp400Tx(49),
                        msrp-TransResp401Tx(50),
                        msrp-TransResp403Tx(51),
                        msrp-TransResp404Tx(52),
                        msrp-TransResp408Tx(53),
                        msrp-TransResp413Tx(54),
                        msrp-TransResp415Tx(55),
                        msrp-TransResp423Tx(56),
                        msrp-TransResp424Tx(57),
                        msrp-TransResp425Tx(58),
                        msrp-TransResp428Tx(59),
                        msrp-TransResp481Tx(60),
                        msrp-TransResp501Tx(61),
                        msrp-TransResp506Tx(62),
                        msrp-AvgSENDTransRx(63),
                        msrp-AvgChatSENDTransRx(64),
                        msrp-AvgIsTypingSENDTransRx(65),
                        msrp-AvgReceiptSENDTransRx(66),
                        msrp-AvgSENDMsgBytesRx(67),
                        msrp-AvgChatSENDMsgBytesRx(68),
                        msrp-AvgIsTypingSENDMsgBytesRx(69),
                        msrp-AvgReceiptSENDMsgBytesRx(70),
                        msrp-SENDMsgBytesRx(71),
                        msrp-ChatSENDMsgBytesRx(72),
                        msrp-IsTypingSENDMsgBytesRx(73),
                        msrp-ReceiptSENDMsgBytesRx(74),
                        msrp-SuccessREPORTTransRx(75),
                        msrp-FailureREPORTTransRx(76),
                        msrp-AvgSuccessREPORTMsgBytesRx(77),
                        msrp-AvgFailureREPORTMsgBytesRx(78),
                        msrp-AvgFailureREPORTRateRx(79),
                        msrp-AvgSuccessREPORTRateRx(80),
                        msrp-REPORTTrans400Rx(81),
                        msrp-REPORTTrans401Rx(82),
                        msrp-REPORTTrans403Rx(83),
                        msrp-REPORTTrans404Rx(84),
                        msrp-REPORTTrans408Rx(85),
                        msrp-REPORTTrans413Rx(86),
                        msrp-REPORTTrans415Rx(87),
                        msrp-REPORTTrans423Rx(88),
                        msrp-REPORTTrans424Rx(89),
                        msrp-REPORTTrans425Rx(90),
                        msrp-REPORTTrans428Rx(91),
                        msrp-REPORTTrans481Rx(92),
                        msrp-REPORTTrans501Rx(93),
                        msrp-REPORTTrans506Rx(94),
                        msrp-AvgFailureREPORTMsgBytes400Rx(95),
                        msrp-AvgFailureREPORTMsgBytes401Rx(96),
                        msrp-AvgFailureREPORTMsgBytes403Rx(97),
                        msrp-AvgFailureREPORTMsgBytes404Rx(98),
                        msrp-AvgFailureREPORTMsgBytes408Rx(99),
                        msrp-AvgFailureREPORTMsgBytes413Rx(100),
                        msrp-AvgFailureREPORTMsgBytes415Rx(101),
                        msrp-AvgFailureREPORTMsgBytes423Rx(102),
                        msrp-AvgFailureREPORTMsgBytes424Rx(103),
                        msrp-AvgFailureREPORTMsgBytes425Rx(104),
                        msrp-AvgFailureREPORTMsgBytes428Rx(105),
                        msrp-AvgFailureREPORTMsgBytes481Rx(106),
                        msrp-AvgFailureREPORTMsgBytes501Rx(107),
                        msrp-AvgFailureREPORTMsgBytes506Rx(108),
                        msrp-TransResponsesRx(109),
                        msrp-SuccessTransResponsesRx(110),
                        msrp-TransResp400Rx(111),
                        msrp-TransResp401Rx(112),
                        msrp-TransResp403Rx(113),
                        msrp-TransResp404Rx(114),
                        msrp-TransResp408Rx(115),
                        msrp-TransResp413Rx(116),
                        msrp-TransResp415Rx(117),
                        msrp-TransResp423Rx(118),
                        msrp-TransResp424Rx(119),
                        msrp-TransResp425Rx(120),
                        msrp-TransResp428Rx(121),
                        msrp-TransResp481Rx(122),
                        msrp-TransResp501Rx(123),
                        msrp-TransResp506Rx(124),
                        msrp-ApMsrpKpiStatsTypeMax(125)
                    }

ApNSEPRealmRvalueDNIndex ::= TEXTUAL-CONVENTION
    STATUS  current
    DESCRIPTION
            "Index of Rvalue and DialedNumber"
    SYNTAX  INTEGER {
                ets0(10),
                ets1(11),
                ets2(12),
                ets3(13),
                ets4(14),
                wps0(20),
                wps1(21),
                wps2(22),
                wps3(23),
                wps4(24),
                q7350(30),
                q7351(31),
                q7352(32),
                q7353(33),
                q7354(34),
                esnet0(40),
                esnet1(41),
                esnet2(42),
                esnet3(43),
                esnet4(44),
                wps0ets0(50),
                wps0ets1(51),
                wps0ets2(52),
                wps0ets3(53),
                wps0ets4(54),
                wps1ets0(55),
                wps1ets1(56),
                wps1ets2(57),
                wps1ets3(58),
                wps1ets4(59),
                wps2ets0(60),
                wps2ets1(61),
                wps2ets2(62),
                wps2ets3(63),
                wps2ets4(64),
                wps3ets0(65),
                wps3ets1(66),
                wps3ets2(67),
                wps3ets3(68),
                wps3ets4(69),
                wps4ets0(70),
                wps4ets1(71),
                wps4ets2(72),
                wps4ets3(73),
                wps4ets4(74),
                dsnroutine(81),
                dsnpriority(82),
                dsnimmediate(83),
                dsnflash(84),
                dsnflashoverride(85),
                drsnroutine(91),
                drsnpriority(92),
                drsnimmediate(93),
                drsnflash(94),
                drsnflashoverride(95),
                drsnflashoverrideoverride(96),
                dialedNumbers(100)
                }
                
ApNSEPRealmStatsType ::= TEXTUAL-CONVENTION
    STATUS  current
    DESCRIPTION
            "Type of NSEP stats"
    SYNTAX  INTEGER {
                inboundactivesessions(1),
                inboundtotalsessions(2),
                inboundhighsessions(3),
                inboundtotalrejectedsessions(4),
                outboundactivesessions(5),
                outboundtotalsessions(6),
                outboundhighsessions(7),
                outboundtotalrejectedsessions(8)
                }
END
