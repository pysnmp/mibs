------------------------------------------------------------------------------
-- ACMEPACKET-SLB-MIB.txt:  Acme Packet Session Load Balancer MIB file
--
-- March 2011
--
-- Copyright (c) by Oracle Communications
-- All rights reserved.
--------------------------------------------------------------------------------
-- This MIB provides a means to gather session load balancer information generated 
-- by Acme Packet Session Load Balancer and SLB cluster members.
-- 

APSLB-MIB DEFINITIONS ::= BEGIN

IMPORTS
	MODULE-IDENTITY, OBJECT-TYPE, NOTIFICATION-TYPE,
	TimeTicks, Integer32, Unsigned32, Counter32, IpAddress
                    FROM SNMPv2-SMI
    InetAddress, InetAddressType, InetAddressPrefixLength, InetVersion, InetZoneIndex 
                    FROM INET-ADDRESS-MIB
    TEXTUAL-CONVENTION
                    FROM SNMPv2-TC
	DisplayString
                    FROM SNMPv2-TC
    MODULE-COMPLIANCE, OBJECT-GROUP, NOTIFICATION-GROUP
					FROM SNMPv2-CONF
	acmepacketMgmt
                    FROM ACMEPACKET-SMI;
     
apSLBModule   MODULE-IDENTITY
		LAST-UPDATED	"201406260000Z"
	    	ORGANIZATION 	"Oracle Communications"
	    	CONTACT-INFO
			"           	Customer Service
		 	Postal:		Oracle Communications
					100 Crosby Drive 
					Bedford, MA 01730
					US
		    	Tel:		1-800-633-0738
			Url:		www.oracle.com
		 	E-mail:		support@oracle.com"
	        DESCRIPTION
			"The Session Load Balancer MIB for Oracle Communications Acme Packet SBCs"
		REVISION 	"201406260000Z" 			
	    	DESCRIPTION
		    	"Updated Organization and Contact info."
		::= { acmepacketMgmt 11 }


   	apSLBMIBObjects OBJECT IDENTIFIER ::= { apSLBModule 1 }
	apSLBNotificationObjects OBJECT IDENTIFIER ::= { apSLBModule 2 }
    apSLBNotificationPrefix OBJECT IDENTIFIER ::= { apSLBModule 3 }
	apSLBConformance OBJECT IDENTIFIER ::= { apSLBModule 4 }	
          
    apSLBNotifications OBJECT IDENTIFIER ::= { apSLBNotificationPrefix 0 }
	apSLBGroups OBJECT IDENTIFIER ::= { apSLBConformance 1 }		
    apSLBNotificationGroups OBJECT IDENTIFIER ::= { apSLBConformance 2 }
	

apSLBMIBGeneralObjects OBJECT IDENTIFIER ::= {apSLBMIBObjects 1}

apSLBStatsEndpointsCurrent    OBJECT-TYPE
        SYNTAX          Unsigned32
        UNITS  		    "endpoints"
        MAX-ACCESS      read-only
        STATUS          current
        DESCRIPTION
                "Number of endpoints currently on the SLB."
        ::= { apSLBMIBGeneralObjects 1 }

apSLBStatsEndpointsDenied    OBJECT-TYPE
        SYNTAX          Unsigned32
        UNITS  		    "endpoints"
        MAX-ACCESS      read-only
        STATUS          current
        DESCRIPTION
                "Number of endpoints denied by the SLB because the
                system has reached the maximum endpoint capacity."
        ::= { apSLBMIBGeneralObjects 2 }

apSLBEndpointCapacity OBJECT-TYPE
	SYNTAX         	Unsigned32
	UNITS  		    "endpoints"
	MAX-ACCESS    	read-only
	STATUS          current
	DESCRIPTION
        		"The maximum number of endpoints allowed on the SLB.  
                This value is based on the installed SLB license(s)."
	::= { apSLBMIBGeneralObjects 3 }

apSLBEndpointCapacityUpperThresh OBJECT-TYPE
	SYNTAX         	Unsigned32 (0..100)
	MAX-ACCESS    	read-only
	STATUS          current
	DESCRIPTION
        		"The configured endpoint capacity upper threshold percentage."
	::= { apSLBMIBGeneralObjects 4 }


apSLBEndpointCapacityLowerThresh OBJECT-TYPE
	SYNTAX         	Unsigned32 (0..100)
	MAX-ACCESS    	read-only
	STATUS          current
	DESCRIPTION
        		"The configured endpoint capacity lower threshold percentage."
	::= { apSLBMIBGeneralObjects 5 }

apSLBStatsUntrustedEndpointsCurrent    OBJECT-TYPE
        SYNTAX          Unsigned32
        UNITS  		    "endpoints"
        MAX-ACCESS      read-only
        STATUS          current
        DESCRIPTION
                "Number of untrusted endpoints currently on the SLB."
        ::= { apSLBMIBGeneralObjects 6 }

apSLBStatsTrustedEndpointsCurrent    OBJECT-TYPE
        SYNTAX          Unsigned32
        UNITS  		    "endpoints"
        MAX-ACCESS      read-only
        STATUS          current
        DESCRIPTION
                "Number of trusted endpoints currently on the SLB."
        ::= { apSLBMIBGeneralObjects 7 }

apSLBStatsUntrustedEndpointsDenied OBJECT-TYPE
	SYNTAX         	Unsigned32
	UNITS  		    "endpoints"
	MAX-ACCESS    	read-only
	STATUS          current
	DESCRIPTION
        		"The number of untrusted endpoints denied by the SLB due
                to the total number of untrusted endpoints exceeding the
                configured maximum allowed."
	::= { apSLBMIBGeneralObjects 8 }

apSLBStatsUntrustedEndpointsAgedOut OBJECT-TYPE
	SYNTAX         	Unsigned32
	UNITS  		    "endpoints"
	MAX-ACCESS    	read-only
	STATUS          current
	DESCRIPTION
        		"The number of untrusted endpoints aged out of the
                system because they were not authenticated within the
                configured grace period."
	::= { apSLBMIBGeneralObjects 9 }

apSLBUntrustedEndpointCapacity OBJECT-TYPE
	SYNTAX         	Unsigned32
	UNITS  		    "endpoints"
	MAX-ACCESS    	read-only
	STATUS          current
	DESCRIPTION
        		"The maximum number of untrusted endpoints allowed on the SLB.  
                This value is a configured percentage of the maximum endpoint
                capacity of the system."
	::= { apSLBMIBGeneralObjects 10 }

apSLBUntrustedEndpointCapacityUpperThresh OBJECT-TYPE
	SYNTAX         	Unsigned32 (0..100)
	MAX-ACCESS    	read-only
	STATUS          current
	DESCRIPTION
        		"The configured untrusted endpoint capacity upper threshold
                percentage."
	::= { apSLBMIBGeneralObjects 11 }

apSLBUntrustedEndpointCapacityLowerThresh OBJECT-TYPE
	SYNTAX         	Unsigned32 (0..100)
	MAX-ACCESS    	read-only
	STATUS          current
	DESCRIPTION
        		"The configured untrusted endpoint capacity lower threshold
                percentage."
	::= { apSLBMIBGeneralObjects 12 }




apSLBEndpointCapacityThresholdTrap NOTIFICATION-TYPE
      OBJECTS         { apSLBStatsEndpointsCurrent,
                        apSLBEndpointCapacity,
                        apSLBEndpointCapacityUpperThresh,
                        apSLBEndpointCapacityLowerThresh
        		      }
      STATUS          current
      DESCRIPTION
	    "The trap will be generated when the number of endpoints on the SLB 
	    exceeds the configured threshold."
      ::= { apSLBNotifications 1 }

apSLBEndpointCapacityThresholdClearTrap NOTIFICATION-TYPE
      OBJECTS         { apSLBStatsEndpointsCurrent,
                        apSLBEndpointCapacity,
                        apSLBEndpointCapacityUpperThresh,
                        apSLBEndpointCapacityLowerThresh
		      }
      STATUS          current
      DESCRIPTION
	    "The trap will be generated when the number of endpoints on the SLB 
	    falls below the configured threshold."
      ::= { apSLBNotifications 2 }

apSLBUntrustedEndpointCapacityThresholdTrap NOTIFICATION-TYPE
      OBJECTS         { apSLBStatsUntrustedEndpointsCurrent,
                        apSLBStatsUntrustedEndpointsDenied,
                        apSLBStatsUntrustedEndpointsAgedOut,
                        apSLBUntrustedEndpointCapacity,
                        apSLBUntrustedEndpointCapacityUpperThresh,
                        apSLBUntrustedEndpointCapacityLowerThresh
        		      }
      STATUS          current
      DESCRIPTION
	    "The trap will be generated when the number of untrusted endpoints
        on the SLB exceeds the configured threshold."
      ::= { apSLBNotifications 3 }

apSLBUntrustedEndpointCapacityThresholdClearTrap NOTIFICATION-TYPE
      OBJECTS         { apSLBStatsUntrustedEndpointsCurrent,
                        apSLBStatsUntrustedEndpointsDenied,
                        apSLBStatsUntrustedEndpointsAgedOut,
                        apSLBUntrustedEndpointCapacity,
                        apSLBUntrustedEndpointCapacityUpperThresh,
                        apSLBUntrustedEndpointCapacityLowerThresh
		      }
      STATUS          current
      DESCRIPTION
	    "The trap will be generated when the number of untrusted endpoints 
        on the SLB falls below the configured threshold."
      ::= { apSLBNotifications 4 }


apSLBEndpointCapacityGroup  OBJECT-GROUP
	OBJECTS {
    apSLBStatsEndpointsCurrent,
    apSLBStatsEndpointsDenied,
    apSLBEndpointCapacity,
    apSLBEndpointCapacityUpperThresh,
    apSLBEndpointCapacityLowerThresh
	    	}
 	STATUS		current
	DESCRIPTION
		"Objects for monitoring SLB endpoint capacity."
	::= {  apSLBGroups 1 }

apSLBUntrustedEndpointCapacityGroup  OBJECT-GROUP
	OBJECTS {
    apSLBStatsUntrustedEndpointsCurrent,
    apSLBStatsTrustedEndpointsCurrent,
    apSLBStatsUntrustedEndpointsDenied,
    apSLBStatsUntrustedEndpointsAgedOut,
    apSLBUntrustedEndpointCapacity,
    apSLBUntrustedEndpointCapacityUpperThresh,
    apSLBUntrustedEndpointCapacityLowerThresh
	    	}
 	STATUS		current
	DESCRIPTION
		"Objects for monitoring SLB untrusted endpoint capacity."
	::= { apSLBGroups 2 }


apSLBEndpointCapacityNotificationsGroup  NOTIFICATION-GROUP
        NOTIFICATIONS {
                        apSLBEndpointCapacityThresholdTrap,
                        apSLBEndpointCapacityThresholdClearTrap
                      }
        STATUS          current
        DESCRIPTION
                "Traps to monitor SLB endpoint capacity threshold crossings."
        ::= { apSLBNotificationGroups 1 }


apSLBUntrustedEndpointCapacityNotificationsGroup  NOTIFICATION-GROUP
        NOTIFICATIONS {
                        apSLBUntrustedEndpointCapacityThresholdTrap,
                        apSLBUntrustedEndpointCapacityThresholdClearTrap
                      }
        STATUS          current
        DESCRIPTION
                "Traps to monitor SLB untrusted endpoint capacity threshold crossings."
        ::= { apSLBNotificationGroups 2 }

END
