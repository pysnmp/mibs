-- CloudGenix, Inc. SMI MIB Copyright (c) 2017 by CloudGenix, Inc.
-- 2017 revision, Aaron Edwards

CLOUDGENIX-SMI DEFINITIONS ::= BEGIN

IMPORTS
    MODULE-COMPLIANCE, OBJECT-GROUP
        FROM SNMPv2-CONF
    MODULE-IDENTITY, OBJECT-IDENTITY, OBJECT-TYPE, enterprises
        FROM SNMPv2-SMI
    ;

cloudgenix MODULE-IDENTITY
    LAST-UPDATED  "201706191800Z" -- June 19, 2017
    ORGANIZATION
        "CloudGenix, Inc."
    CONTACT-INFO
        "CloudGenix Support

         2665 N First Street
         Suite 110
         San Jose, CA 95134
         USA

         +1 844 800 CGNX

         support@cloudgenix.com"
    DESCRIPTION
        "Structure of Management Information for CloudGenix"
    REVISION      "201706191800Z" -- June 19, 2017
    DESCRIPTION
        "Inital Revision"
    ::= { enterprises 50114 }

cgxObjects OBJECT IDENTIFIER ::= { cloudgenix 1 }

cgxConformance OBJECT IDENTIFIER ::= { cloudgenix 2 }

cgxCompliances OBJECT IDENTIFIER ::= { cgxConformance 1 }

cloudgenixCompliance MODULE-COMPLIANCE
    STATUS         current
    DESCRIPTION
        "Compliance statement for entities which implement the
         CloudGenix SMI MIB"

    MODULE         CLOUDGENIX-SMI
    ::= { cgxCompliances 1 }

cgxGroups OBJECT IDENTIFIER ::= { cgxConformance 2 }

cgxMgmt OBJECT IDENTIFIER ::= { cloudgenix 10 }

END
