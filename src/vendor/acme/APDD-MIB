-------------------------------------------------------------------------------
-- APDD-MIB.txt:  Acme Packet Diameter Director MIB
--
-- June 2011
--
-- Copyright (c) by Oracle Communications
-- All rights reserved.
-------------------------------------------------------------------------------
-- 

APDD-MIB DEFINITIONS ::= BEGIN

IMPORTS
	MODULE-IDENTITY, OBJECT-TYPE, NOTIFICATION-TYPE,
	Integer32, Gauge32, Counter32
                    FROM SNMPv2-SMI
        TEXTUAL-CONVENTION, DisplayString, TruthValue
                    FROM SNMPv2-TC
        MODULE-COMPLIANCE, OBJECT-GROUP, NOTIFICATION-GROUP
					FROM SNMPv2-CONF
	ApTransportType
		    FROM ACMEPACKET-TC
	acmepacketMgmt
                    FROM ACMEPACKET-SMI;
     
apDDModule   MODULE-IDENTITY
		LAST-UPDATED	"201406260000Z"
	    	ORGANIZATION 	"Oracle Communications"
	    	CONTACT-INFO
			"           	Customer Service
		 	Postal:		Oracle Communications
					100 Crosby Drive 
					Bedford, MA 01730
					US
		    	Tel:		1-800-633-0738
			Url:		www.oracle.com
		 	E-mail:		support@oracle.com"
		DESCRIPTION
		    "The Policy Director MIB for Oracle Communications Acme Packet SBCs"
                REVISION "201406260000Z" 			
                DESCRIPTION
			"Updated Organization and Contact info."
		::= { acmepacketMgmt 12 }


apDDMIBObjects OBJECT IDENTIFIER ::= { apDDModule 1 }
apDDMIBGeneralObjects OBJECT IDENTIFIER ::= {apDDMIBObjects 1}
apDDMIBTabularObjects OBJECT IDENTIFIER ::= {apDDMIBObjects 2}

apDDNotificationObjects OBJECT IDENTIFIER ::= { apDDModule 2 }
apDDNotifObjects OBJECT IDENTIFIER ::= { apDDNotificationObjects 1 }
apDDNotifPrefix  OBJECT IDENTIFIER ::= { apDDNotificationObjects 2 }
apDDNotifications  OBJECT IDENTIFIER ::= { apDDNotifPrefix 0 }

-- conformance information

apDDConformance OBJECT IDENTIFIER ::= { apDDModule 3 }	
apDDObjectGroups OBJECT IDENTIFIER ::= { apDDConformance 1 }		
apDDNotificationGroups OBJECT IDENTIFIER ::= { apDDConformance 2 }

-- values for apDdInterfaceStatus and apDdAgentStatus

ApDdStatusOptions ::= TEXTUAL-CONVENTION
	STATUS		current
	DESCRIPTION
	    "Integer representation of DD Interfaces and Agents status."
	SYNTAX		INTEGER {    
				outOfService(0),
				inService(1),
				constraintsExceeded(2)
			}

-- Start of General Object

apDdInterfaceNumber    OBJECT-TYPE
        SYNTAX          Integer32
        MAX-ACCESS      read-only
        STATUS          current
        DESCRIPTION
	    "Number of the DD interfaces in the system."
        ::= { apDDMIBGeneralObjects 1 }

apDdCurrentTransRate	OBJECT-TYPE
	SYNTAX		Gauge32
	UNITS "per10Seconds"
	MAX-ACCESS 	read-only
	STATUS		current
	DESCRIPTION
	    "The number of transactions over a 10s period."
	::= {apDDMIBGeneralObjects 2}

apDdHighTransRate	OBJECT-TYPE
	SYNTAX		Gauge32
	UNITS "per10Seconds"
	MAX-ACCESS 	read-only
	STATUS		current
	DESCRIPTION
	    "Maximum value of apDdCurrentTransRate across all 10s periods."
	::= {apDDMIBGeneralObjects 3}

apDdLowTransRate	OBJECT-TYPE
	SYNTAX		Gauge32
	UNITS "per10Seconds"
	MAX-ACCESS 	read-only
	STATUS		current
	DESCRIPTION
	    "Mimimum value of apDdCurrentTransRate across all 10s periods."
	::= {apDDMIBGeneralObjects 4}

apDdAgentNumber    OBJECT-TYPE
        SYNTAX          Integer32
        MAX-ACCESS      read-only
        STATUS          current
        DESCRIPTION
	    "Number of the DD Agents in the system."
        ::= { apDDMIBGeneralObjects 5 }

--  Start of Session Stats

apDdSessionPeriodActive    OBJECT-TYPE
        SYNTAX          Integer32
        MAX-ACCESS      read-only
        STATUS          current
        DESCRIPTION
	    "Number of the DD session is Active in this period"
        ::= { apDDMIBGeneralObjects 6 }

apDdSessionPeriodHigh    OBJECT-TYPE
        SYNTAX          Integer32
        MAX-ACCESS      read-only
        STATUS          current
        DESCRIPTION
	    "Highest number of the DD session in this period"
        ::= { apDDMIBGeneralObjects 7 }

apDdSessionPeriodTotal    OBJECT-TYPE
        SYNTAX          Integer32
        MAX-ACCESS      read-only
        STATUS          current
        DESCRIPTION
	    "Total Number of the DD session in this period"
        ::= { apDDMIBGeneralObjects 8 }

apDdSessionLifeTotal    OBJECT-TYPE
        SYNTAX          Integer32
        MAX-ACCESS      read-only
        STATUS          current
        DESCRIPTION
	    "Total Number of the DD session in life"
        ::= { apDDMIBGeneralObjects 9 }

apDdSessionLifePerMax    OBJECT-TYPE
        SYNTAX          Integer32
        MAX-ACCESS      read-only
        STATUS          current
        DESCRIPTION
	    "PerMax number of the DD session in life"
        ::= { apDDMIBGeneralObjects 10 }

apDdSessionLifeHigh    OBJECT-TYPE
        SYNTAX          Integer32
        MAX-ACCESS      read-only
        STATUS          current
        DESCRIPTION
	    "Highest number of the DD session in life"
        ::= { apDDMIBGeneralObjects 11 }


apDdSessInitPeriodActive    OBJECT-TYPE
        SYNTAX          Integer32
        MAX-ACCESS      read-only
        STATUS          current
        DESCRIPTION
	    "Number of the DD session is Active in Initial state in this period"
        ::= { apDDMIBGeneralObjects 12 }

apDdSessInitPeriodHigh    OBJECT-TYPE
        SYNTAX          Integer32
        MAX-ACCESS      read-only
        STATUS          current
        DESCRIPTION
	    "Highest number of the DD session in Initial state in this period"
        ::= { apDDMIBGeneralObjects 13 }

apDdSessInitPeriodTotal    OBJECT-TYPE
        SYNTAX          Integer32
        MAX-ACCESS      read-only
        STATUS          current
        DESCRIPTION
	    "Total Number of the DD session in Initial state in this period"
        ::= { apDDMIBGeneralObjects 14 }

apDdSessInitLifeTotal    OBJECT-TYPE
        SYNTAX          Integer32
        MAX-ACCESS      read-only
        STATUS          current
        DESCRIPTION
	    "Total Number of the DD session in Initial state in life"
        ::= { apDDMIBGeneralObjects 15 }

apDdSessInitLifePerMax    OBJECT-TYPE
        SYNTAX          Integer32
        MAX-ACCESS      read-only
        STATUS          current
        DESCRIPTION
	    "PerMax number of the DD session in Initial state in life"
        ::= { apDDMIBGeneralObjects 16 }

apDdSessInitLifeHigh    OBJECT-TYPE
        SYNTAX          Integer32
        MAX-ACCESS      read-only
        STATUS          current
        DESCRIPTION
	    "Highest number of the DD session in Initial state in life"
        ::= { apDDMIBGeneralObjects 17 }

apDdSessEstablishedPeriodActive    OBJECT-TYPE
        SYNTAX          Integer32
        MAX-ACCESS      read-only
        STATUS          current
        DESCRIPTION
	    "Number of the DD session is Active in Established state in this period"
        ::= { apDDMIBGeneralObjects 18 }

apDdSessEstablishedPeriodHigh    OBJECT-TYPE
        SYNTAX          Integer32
        MAX-ACCESS      read-only
        STATUS          current
        DESCRIPTION
	    "Highest number of the DD session in Established state in this period"
        ::= { apDDMIBGeneralObjects 19 }

apDdSessEstablishedPeriodTotal    OBJECT-TYPE
        SYNTAX          Integer32
        MAX-ACCESS      read-only
        STATUS          current
        DESCRIPTION
	    "Total Number of the DD session in Established state in this period"
        ::= { apDDMIBGeneralObjects 20 }

apDdSessEstablishedLifeTotal    OBJECT-TYPE
        SYNTAX          Integer32
        MAX-ACCESS      read-only
        STATUS          current
        DESCRIPTION
	    "Total Number of the DD session in Established state in life"
        ::= { apDDMIBGeneralObjects 21 }

apDdSessEstablishedLifePerMax    OBJECT-TYPE
        SYNTAX          Integer32
        MAX-ACCESS      read-only
        STATUS          current
        DESCRIPTION
	    "PerMax number of the DD session in Established state in life"
        ::= { apDDMIBGeneralObjects 22 }

apDdSessEstablishedLifeHigh    OBJECT-TYPE
        SYNTAX          Integer32
        MAX-ACCESS      read-only
        STATUS          current
        DESCRIPTION
	    "Highest number of the DD session in Established state in life"
        ::= { apDDMIBGeneralObjects 23 }

apDdSessTerminatedPeriodActive    OBJECT-TYPE
        SYNTAX          Integer32
        MAX-ACCESS      read-only
        STATUS          current
        DESCRIPTION
	    "Number of the DD session is Active in Terminated state in this period"
        ::= { apDDMIBGeneralObjects 24 }

apDdSessTerminatedPeriodHigh    OBJECT-TYPE
        SYNTAX          Integer32
        MAX-ACCESS      read-only
        STATUS          current
        DESCRIPTION
	    "Highest number of the DD session in Terminated state in this period"
        ::= { apDDMIBGeneralObjects 25 }

apDdSessTerminatedPeriodTotal    OBJECT-TYPE
        SYNTAX          Integer32
        MAX-ACCESS      read-only
        STATUS          current
        DESCRIPTION
	    "Total Number of the DD session in Terminated state in this period"
        ::= { apDDMIBGeneralObjects 26 }

apDdSessTerminatedLifeTotal    OBJECT-TYPE
        SYNTAX          Integer32
        MAX-ACCESS      read-only
        STATUS          current
        DESCRIPTION
	    "Total Number of the DD session in Terminated state in life"
        ::= { apDDMIBGeneralObjects 27 }

apDdSessTerminatedLifePerMax    OBJECT-TYPE
        SYNTAX          Integer32
        MAX-ACCESS      read-only
        STATUS          current
        DESCRIPTION
	    "PerMax number of the DD session in Terminated state in life"
        ::= { apDDMIBGeneralObjects 28 }

apDdSessTerminatedLifeHigh    OBJECT-TYPE
        SYNTAX          Integer32
        MAX-ACCESS      read-only
        STATUS          current
        DESCRIPTION
	    "Highest number of the DD session in Terminated state in life"
        ::= { apDDMIBGeneralObjects 29 }


apDdSessTimeoutPeriodTotal    OBJECT-TYPE
        SYNTAX          Integer32
        MAX-ACCESS      read-only
        STATUS          current
        DESCRIPTION
	    "Total Number of the DD session in Timeout state in this period"
        ::= { apDDMIBGeneralObjects 30 }

apDdSessTimeoutLifeTotal    OBJECT-TYPE
        SYNTAX          Integer32
        MAX-ACCESS      read-only
        STATUS          current
        DESCRIPTION
	    "Total Number of the DD session in Timeout state in life"
        ::= { apDDMIBGeneralObjects 31 }

apDdSessTimeoutLifePerMax    OBJECT-TYPE
        SYNTAX          Integer32
        MAX-ACCESS      read-only
        STATUS          current
        DESCRIPTION
	    "PerMax number of the DD session in Timeout state in life"
        ::= { apDDMIBGeneralObjects 32 }


apDdSessErrorsPeriodTotal    OBJECT-TYPE
        SYNTAX          Integer32
        MAX-ACCESS      read-only
        STATUS          current
        DESCRIPTION
	    "Total Number of the DD session in Errors state in this period"
        ::= { apDDMIBGeneralObjects 33 }

apDdSessErrorsLifeTotal    OBJECT-TYPE
        SYNTAX          Integer32
        MAX-ACCESS      read-only
        STATUS          current
        DESCRIPTION
	    "Total Number of the DD session in Errors state in life"
        ::= { apDDMIBGeneralObjects 34 }

apDdSessErrorsLifePerMax    OBJECT-TYPE
        SYNTAX          Integer32
        MAX-ACCESS      read-only
        STATUS          current
        DESCRIPTION
	    "PerMax number of the DD session in Errors state in life"
        ::= { apDDMIBGeneralObjects 35 }


apDdSessMissPeriodTotal    OBJECT-TYPE
        SYNTAX          Integer32
        MAX-ACCESS      read-only
        STATUS          current
        DESCRIPTION
	    "Total Number of the DD session in Miss state in this period"
        ::= { apDDMIBGeneralObjects 36 }

apDdSessMissLifeTotal    OBJECT-TYPE
        SYNTAX          Integer32
        MAX-ACCESS      read-only
        STATUS          current
        DESCRIPTION
	    "Total Number of the DD session in Miss state in life"
        ::= { apDDMIBGeneralObjects 37 }

apDdSessMissLifePerMax    OBJECT-TYPE
        SYNTAX          Integer32
        MAX-ACCESS      read-only
        STATUS          current
        DESCRIPTION
	    "PerMax number of the DD session in Miss state in life"
        ::= { apDDMIBGeneralObjects 38 }


--  End of Session Stats


--  Start of Subscriber Stats

apDdSubscriberPeriodActive    OBJECT-TYPE
        SYNTAX          Integer32
        MAX-ACCESS      read-only
        STATUS          current
        DESCRIPTION
	    "Number of the DD subscriber is Active in this period"
        ::= { apDDMIBGeneralObjects 100 }

apDdSubscriberPeriodHigh    OBJECT-TYPE
        SYNTAX          Integer32
        MAX-ACCESS      read-only
        STATUS          current
        DESCRIPTION
	    "Highest number of the DD subscriber in this period"
        ::= { apDDMIBGeneralObjects 101 }

apDdSubscriberPeriodTotal    OBJECT-TYPE
        SYNTAX          Integer32
        MAX-ACCESS      read-only
        STATUS          current
        DESCRIPTION
	    "Total Number of the DD subscriber in this period"
        ::= { apDDMIBGeneralObjects 102 }

apDdSubscriberLifeTotal    OBJECT-TYPE
        SYNTAX          Integer32
        MAX-ACCESS      read-only
        STATUS          current
        DESCRIPTION
	    "Total Number of the DD subscriber in life"
        ::= { apDDMIBGeneralObjects 103 }

apDdSubscriberLifePerMax    OBJECT-TYPE
        SYNTAX          Integer32
        MAX-ACCESS      read-only
        STATUS          current
        DESCRIPTION
	    "PerMax number of the DD subscriber in life"
        ::= { apDDMIBGeneralObjects 104 }

apDdSubscriberLifeHigh    OBJECT-TYPE
        SYNTAX          Integer32
        MAX-ACCESS      read-only
        STATUS          current
        DESCRIPTION
	    "Highest number of the DD subscriber in life"
        ::= { apDDMIBGeneralObjects 105 }


apDdSubscribePeriodActive    OBJECT-TYPE
        SYNTAX          Integer32
        MAX-ACCESS      read-only
        STATUS          current
        DESCRIPTION
	    "Number of the DD subscriber is Active in Initial state in this period"
        ::= { apDDMIBGeneralObjects 106 }

apDdSubscribePeriodHigh    OBJECT-TYPE
        SYNTAX          Integer32
        MAX-ACCESS      read-only
        STATUS          current
        DESCRIPTION
	    "Highest number of the DD subscriber in Initial state in this period"
        ::= { apDDMIBGeneralObjects 107 }

apDdSubscribePeriodTotal    OBJECT-TYPE
        SYNTAX          Integer32
        MAX-ACCESS      read-only
        STATUS          current
        DESCRIPTION
	    "Total Number of the DD subscriber in Initial state in this period"
        ::= { apDDMIBGeneralObjects 108 }

apDdSubscribeLifeTotal    OBJECT-TYPE
        SYNTAX          Integer32
        MAX-ACCESS      read-only
        STATUS          current
        DESCRIPTION
	    "Total Number of the DD subscriber in Initial state in life"
        ::= { apDDMIBGeneralObjects 109 }

apDdSubscribeLifePerMax    OBJECT-TYPE
        SYNTAX          Integer32
        MAX-ACCESS      read-only
        STATUS          current
        DESCRIPTION
	    "PerMax number of the DD subscriber in Initial state in life"
        ::= { apDDMIBGeneralObjects 110 }

apDdSubscribeLifeHigh    OBJECT-TYPE
        SYNTAX          Integer32
        MAX-ACCESS      read-only
        STATUS          current
        DESCRIPTION
	    "Highest number of the DD subscriber in Initial state in life"
        ::= { apDDMIBGeneralObjects 111 }

apDdUnsubscribePeriodActive    OBJECT-TYPE
        SYNTAX          Integer32
        MAX-ACCESS      read-only
        STATUS          current
        DESCRIPTION
	    "Number of the DD subscriber is Active in Established state in this period"
        ::= { apDDMIBGeneralObjects 112 }

apDdUnsubscribePeriodHigh    OBJECT-TYPE
        SYNTAX          Integer32
        MAX-ACCESS      read-only
        STATUS          current
        DESCRIPTION
	    "Highest number of the DD subscriber in Established state in this period"
        ::= { apDDMIBGeneralObjects 113 }

apDdUnsubscribePeriodTotal    OBJECT-TYPE
        SYNTAX          Integer32
        MAX-ACCESS      read-only
        STATUS          current
        DESCRIPTION
	    "Total Number of the DD subscriber in Established state in this period"
        ::= { apDDMIBGeneralObjects 114 }

apDdUnsubscribeLifeTotal    OBJECT-TYPE
        SYNTAX          Integer32
        MAX-ACCESS      read-only
        STATUS          current
        DESCRIPTION
	    "Total Number of the DD subscriber in Established state in life"
        ::= { apDDMIBGeneralObjects 115 }

apDdUnsubscribeLifePerMax    OBJECT-TYPE
        SYNTAX          Integer32
        MAX-ACCESS      read-only
        STATUS          current
        DESCRIPTION
	    "PerMax number of the DD subscriber in Established state in life"
        ::= { apDDMIBGeneralObjects 116 }

apDdUnsubscribeLifeHigh    OBJECT-TYPE
        SYNTAX          Integer32
        MAX-ACCESS      read-only
        STATUS          current
        DESCRIPTION
	    "Highest number of the DD subscriber in Established state in life"
        ::= { apDDMIBGeneralObjects 117 }

apDdPolicyHitPeriodActive    OBJECT-TYPE
        SYNTAX          Integer32
        MAX-ACCESS      read-only
        STATUS          current
        DESCRIPTION
	    "Number of the DD subscriber is Active in Terminated state in this period"
        ::= { apDDMIBGeneralObjects 118 }

apDdPolicyHitPeriodHigh    OBJECT-TYPE
        SYNTAX          Integer32
        MAX-ACCESS      read-only
        STATUS          current
        DESCRIPTION
	    "Highest number of the DD subscriber in Terminated state in this period"
        ::= { apDDMIBGeneralObjects 119 }

apDdPolicyHitPeriodTotal    OBJECT-TYPE
        SYNTAX          Integer32
        MAX-ACCESS      read-only
        STATUS          current
        DESCRIPTION
	    "Total Number of the DD subscriber in Terminated state in this period"
        ::= { apDDMIBGeneralObjects 120 }

apDdPolicyHitLifeTotal    OBJECT-TYPE
        SYNTAX          Integer32
        MAX-ACCESS      read-only
        STATUS          current
        DESCRIPTION
	    "Total Number of the DD subscriber in Terminated state in life"
        ::= { apDDMIBGeneralObjects 121 }

apDdPolicyHitLifePerMax    OBJECT-TYPE
        SYNTAX          Integer32
        MAX-ACCESS      read-only
        STATUS          current
        DESCRIPTION
	    "PerMax number of the DD subscriber in Terminated state in life"
        ::= { apDDMIBGeneralObjects 122 }

apDdPolicyHitLifeHigh    OBJECT-TYPE
        SYNTAX          Integer32
        MAX-ACCESS      read-only
        STATUS          current
        DESCRIPTION
	    "Highest number of the DD subscriber in Terminated state in life"
        ::= { apDDMIBGeneralObjects 123 }

apDdPolicyMissPeriodActive    OBJECT-TYPE
        SYNTAX          Integer32
        MAX-ACCESS      read-only
        STATUS          current
        DESCRIPTION
	    "Number of the DD subscriber is Active in Timeout state in this period"
        ::= { apDDMIBGeneralObjects 124 }

apDdPolicyMissPeriodHigh    OBJECT-TYPE
        SYNTAX          Integer32
        MAX-ACCESS      read-only
        STATUS          current
        DESCRIPTION
	    "Highest number of the DD subscriber in Timeout state in this period"
        ::= { apDDMIBGeneralObjects 125 }

apDdPolicyMissPeriodTotal    OBJECT-TYPE
        SYNTAX          Integer32
        MAX-ACCESS      read-only
        STATUS          current
        DESCRIPTION
	    "Total Number of the DD subscriber in Timeout state in this period"
        ::= { apDDMIBGeneralObjects 126 }

apDdPolicyMissLifeTotal    OBJECT-TYPE
        SYNTAX          Integer32
        MAX-ACCESS      read-only
        STATUS          current
        DESCRIPTION
	    "Total Number of the DD subscriber in Timeout state in life"
        ::= { apDDMIBGeneralObjects 127 }

apDdPolicyMissLifePerMax    OBJECT-TYPE
        SYNTAX          Integer32
        MAX-ACCESS      read-only
        STATUS          current
        DESCRIPTION
	    "PerMax number of the DD subscriber in Timeout state in life"
        ::= { apDDMIBGeneralObjects 128 }

apDdPolicyMissLifeHigh    OBJECT-TYPE
        SYNTAX          Integer32
        MAX-ACCESS      read-only
        STATUS          current
        DESCRIPTION
	    "Highest number of the DD subscriber in Timeout state in life"
        ::= { apDDMIBGeneralObjects 129 }

apDdSubscriberMissPeriodTotal    OBJECT-TYPE
        SYNTAX          Integer32
        MAX-ACCESS      read-only
        STATUS          current
        DESCRIPTION
	    "Total Number of the DD subscriber in Errors state in this period"
        ::= { apDDMIBGeneralObjects 130 }

apDdSubscriberMissLifeTotal    OBJECT-TYPE
        SYNTAX          Integer32
        MAX-ACCESS      read-only
        STATUS          current
        DESCRIPTION
	    "Total Number of the DD subscriber in Errors state in life"
        ::= { apDDMIBGeneralObjects 131 }

apDdSubscriberMissLifePerMax    OBJECT-TYPE
        SYNTAX          Integer32
        MAX-ACCESS      read-only
        STATUS          current
        DESCRIPTION
	    "PerMax number of the DD subscriber in Errors state in life"
        ::= { apDDMIBGeneralObjects 132 }


--  End of Subscriber Stats


-- End of General Object

-- Start of Interface Tabular Object

apDdInterfaceStatsTable       	OBJECT-TYPE
        SYNTAX          SEQUENCE OF ApDdInterfaceStatsEntry
        MAX-ACCESS      not-accessible
        STATUS          current
        DESCRIPTION
	    "DD interface statistics."
        ::= { apDDMIBTabularObjects 1}

apDdInterfaceStatsEntry         OBJECT-TYPE
        SYNTAX          ApDdInterfaceStatsEntry
        MAX-ACCESS      not-accessible
        STATUS          current
        DESCRIPTION
	    "A table entry designed to hold per DD interface statistics."
        INDEX { apDdInterfaceIndex }
        ::= { apDdInterfaceStatsTable 1 }

ApDdInterfaceStatsEntry ::= SEQUENCE {
        apDdInterfaceIndex           		INTEGER,
        apDdInterfaceRealmName		        DisplayString,
        apDdClientTransCPActive                Gauge32,
        apDdClientTransCPHigh                  Counter32,
        apDdClientTransCPTotal                 Counter32,
        apDdClientTransLTTotal                 Counter32,
        apDdClientTransLTPerMax                Counter32,
        apDdClientTransLTHigh                  Counter32,
        apDdServerTransCPActive                Gauge32,
        apDdServerTransCPHigh                  Counter32,
        apDdServerTransCPTotal                 Counter32,
        apDdServerTransLTTotal                 Counter32,
        apDdServerTransLTPerMax                Counter32,
        apDdServerTransLTHigh                  Counter32,
        apDdGenSocketsCPActive                 Gauge32,
        apDdGenSocketsCPHigh                   Counter32,
        apDdGenSocketsCPTotal                  Counter32,
        apDdGenSocketsLTTotal                  Counter32,
        apDdGenSocketsLTPerMax                 Counter32,
        apDdGenSocketsLTHigh                   Counter32,
        apDdGenConnectsCPActive                Gauge32,
        apDdGenConnectsCPHigh                  Counter32,
        apDdGenConnectsCPTotal                 Counter32,
        apDdGenConnectsLTTotal                 Counter32,
        apDdGenConnectsLTPerMax                Counter32,
        apDdGenConnectsLTHigh                  Counter32,
        apDdInterfaceStatus                    ApDdStatusOptions
}

apDdInterfaceIndex		OBJECT-TYPE
        SYNTAX			INTEGER (1..2147483647)
        MAX-ACCESS		accessible-for-notify
        STATUS			current
        DESCRIPTION
	    "An integer for the sole purpose of indexing the DD interface."
	::= {apDdInterfaceStatsEntry 1}

apDdInterfaceRealmName		OBJECT-TYPE
	SYNTAX 			DisplayString (SIZE (0..255))
	MAX-ACCESS		read-only
	STATUS			current
	DESCRIPTION
	    "Realm name of the DD interface if the row is for per interface 
	    stats. Otherwise, it is an empty string."
	::= {apDdInterfaceStatsEntry 2}

apDdClientTransCPActive	OBJECT-TYPE
	SYNTAX		Gauge32
	MAX-ACCESS 	read-only
	STATUS		current
	DESCRIPTION
	    "Number of active client transactions in the current period."
	::= {apDdInterfaceStatsEntry 3}

apDdClientTransCPHigh	OBJECT-TYPE
	SYNTAX		Counter32
	MAX-ACCESS 	read-only
	STATUS		current
	DESCRIPTION
	    "Maximum value of apDdClientTransCPActive in the current period (high water mark).  "
	::= {apDdInterfaceStatsEntry 4}

apDdClientTransCPTotal	OBJECT-TYPE
	SYNTAX		Counter32
	MAX-ACCESS 	read-only
	STATUS		current
	DESCRIPTION
	    "Total number of client transactions in the current period."
	::= {apDdInterfaceStatsEntry 5}

apDdClientTransLTTotal	OBJECT-TYPE
	SYNTAX		Counter32
	MAX-ACCESS 	read-only
	STATUS		current
	DESCRIPTION
	    "Total number of transactions in client side in life time."
	::= {apDdInterfaceStatsEntry 6}

apDdClientTransLTPerMax	OBJECT-TYPE
	SYNTAX		Counter32
	MAX-ACCESS 	read-only
	STATUS		current
	DESCRIPTION
	    "Maximum value of apDdClientTransCPTotal across all periods (high water mark)."
	::= {apDdInterfaceStatsEntry 7}

apDdClientTransLTHigh	OBJECT-TYPE
	SYNTAX		Counter32
	MAX-ACCESS 	read-only
	STATUS		current
	DESCRIPTION
	    "Maximum value of apDdClientTransCPHigh across all periods (high water mark)."
	::= {apDdInterfaceStatsEntry 8}

apDdServerTransCPActive	OBJECT-TYPE
	SYNTAX		Gauge32
	MAX-ACCESS 	read-only
	STATUS		current
	DESCRIPTION
	    "Number of active transactions in server side in current period."
	::= {apDdInterfaceStatsEntry 9}

apDdServerTransCPHigh	OBJECT-TYPE
	SYNTAX		Counter32
	MAX-ACCESS 	read-only
	STATUS		current
	DESCRIPTION
	    "Highest number of active transactions in server side in current period."
	::= {apDdInterfaceStatsEntry 10}

apDdServerTransCPTotal	OBJECT-TYPE
	SYNTAX		Counter32
	MAX-ACCESS 	read-only
	STATUS		current
	DESCRIPTION
	    "Total number of transactions in server side in current period."
	::= {apDdInterfaceStatsEntry 11}

apDdServerTransLTTotal	OBJECT-TYPE
	SYNTAX		Counter32
	MAX-ACCESS 	read-only
	STATUS		current
	DESCRIPTION
	    "Total number of transactions in server side in life time."
	::= {apDdInterfaceStatsEntry 12}

apDdServerTransLTPerMax	OBJECT-TYPE
	SYNTAX		Counter32
	MAX-ACCESS 	read-only
	STATUS		current
	DESCRIPTION
	    "Maximum value of apDdServerTransCPTotal across all periods (high water mark)."
	::= {apDdInterfaceStatsEntry 13}

apDdServerTransLTHigh	OBJECT-TYPE
	SYNTAX		Counter32
	MAX-ACCESS 	read-only
	STATUS		current
	DESCRIPTION
	    "Maximum value of apDdServerTransCPHigh across all periods (high water mark)."
	::= {apDdInterfaceStatsEntry 14}

apDdGenSocketsCPActive	OBJECT-TYPE
	SYNTAX		Gauge32
	MAX-ACCESS 	read-only
	STATUS		current
	DESCRIPTION
	    "Number of active sockets in current period."
	::= {apDdInterfaceStatsEntry 15}

apDdGenSocketsCPHigh	OBJECT-TYPE
	SYNTAX		Counter32
	MAX-ACCESS 	read-only
	STATUS		current
	DESCRIPTION
	    "Highest number of active sockets in current period."
	::= {apDdInterfaceStatsEntry 16}

apDdGenSocketsCPTotal	OBJECT-TYPE
	SYNTAX		Counter32
	MAX-ACCESS 	read-only
	STATUS		current
	DESCRIPTION
	    "Total number of sockets in current period."
	::= {apDdInterfaceStatsEntry 17}

apDdGenSocketsLTTotal	OBJECT-TYPE
	SYNTAX		Counter32
	MAX-ACCESS 	read-only
	STATUS		current
	DESCRIPTION
	    "Total number of sockets in life time."
	::= {apDdInterfaceStatsEntry 18}

apDdGenSocketsLTPerMax	OBJECT-TYPE
	SYNTAX		Counter32
	MAX-ACCESS 	read-only
	STATUS		current
	DESCRIPTION
	    "Maximum value of apDdSocketsCPTotal across all periods (high water mark)."
	::= {apDdInterfaceStatsEntry 19}

apDdGenSocketsLTHigh	OBJECT-TYPE
	SYNTAX		Counter32
	MAX-ACCESS 	read-only
	STATUS		current
	DESCRIPTION
	    "Maximum value of apDdSocketsCPHigh across all periods (high water mark)."
	::= {apDdInterfaceStatsEntry 20}

apDdGenConnectsCPActive	OBJECT-TYPE
	SYNTAX		Gauge32
	MAX-ACCESS 	read-only
	STATUS		current
	DESCRIPTION
	    "Number of active connections in current period."
	::= {apDdInterfaceStatsEntry 21}

apDdGenConnectsCPHigh	OBJECT-TYPE
	SYNTAX		Counter32
	MAX-ACCESS 	read-only
	STATUS		current
	DESCRIPTION
	    "high number of connections in current period."
	::= {apDdInterfaceStatsEntry 22}

apDdGenConnectsCPTotal	OBJECT-TYPE
	SYNTAX		Counter32
	MAX-ACCESS 	read-only
	STATUS		current
	DESCRIPTION
	    "Total number of connections in current period."
	::= {apDdInterfaceStatsEntry 23}

apDdGenConnectsLTTotal	OBJECT-TYPE
	SYNTAX		Counter32
	MAX-ACCESS 	read-only
	STATUS		current
	DESCRIPTION
	    "Total number of connections in life time."
	::= {apDdInterfaceStatsEntry 24}

apDdGenConnectsLTPerMax	OBJECT-TYPE
	SYNTAX		Counter32
	MAX-ACCESS 	read-only
	STATUS		current
	DESCRIPTION
	    "Maximum value of apDdConnectsCPTotal across all periods (high water mark)."
	::= {apDdInterfaceStatsEntry 25}

apDdGenConnectsLTHigh	OBJECT-TYPE
	SYNTAX		Counter32
	MAX-ACCESS 	read-only
	STATUS		current
	DESCRIPTION
	    "Maximum value of apDdConnectsCPHigh across all periods (high water mark)."
	::= {apDdInterfaceStatsEntry 26}

apDdInterfaceStatus	OBJECT-TYPE
	SYNTAX		ApDdStatusOptions
	MAX-ACCESS	read-only
	STATUS		current
	DESCRIPTION
	    "Status of the DD Interfaces in the system."
	::= {apDdInterfaceStatsEntry 27}

apDdErrorStatusTable       	OBJECT-TYPE
        SYNTAX          SEQUENCE OF ApDdErrorStatusEntry
        MAX-ACCESS      not-accessible
        STATUS          current
        DESCRIPTION
	    "per DD interface error stats."
        ::= { apDDMIBTabularObjects 2 }

apDdErrorStatusEntry         OBJECT-TYPE
        SYNTAX          ApDdErrorStatusEntry
        MAX-ACCESS      not-accessible
        STATUS          current
        DESCRIPTION
	    "A table entry designed to hold error status data"
        INDEX { apDdInterfaceIndex }
        ::= { apDdErrorStatusTable 1 }

ApDdErrorStatusEntry ::= SEQUENCE {
        apDdNoRouteFoundRecent                        Gauge32,
        apDdNoRouteFoundTotal                         Counter32,
        apDdNoRouteFoundPerMax                        Counter32,
        apDdMalformedMsgRecent                        Gauge32,
        apDdMalformedMsgTotal                         Counter32,
        apDdMalformedMsgPerMax                        Counter32,
        apDdRejectedMsgRecent                         Gauge32,
        apDdRejectedMsgTotal                          Counter32,
        apDdRejectedMsgPerMax                         Counter32,
        apDdDroppedMsgRecent                          Gauge32,
        apDdDroppedMsgTotal                           Counter32,
        apDdDroppedMsgPerMax                          Counter32,
        apDdInboundConstraintsRecent                  Gauge32,
        apDdInboundConstraintsTotal                   Counter32,
        apDdInboundConstraintsPerMax                  Counter32,
        apDdOutboundConstraintsRecent                 Gauge32,
        apDdOutboundConstraintsTotal                  Counter32,
        apDdOutboundConstraintsPerMax                 Counter32
}

apDdNoRouteFoundRecent	OBJECT-TYPE
	SYNTAX		Gauge32
	MAX-ACCESS 	read-only
	STATUS		current
	DESCRIPTION
	    "Number of 'no route found' error in recent period."
	::= {apDdErrorStatusEntry 1}

apDdNoRouteFoundTotal	OBJECT-TYPE
	SYNTAX		Counter32
	MAX-ACCESS 	read-only
	STATUS		current
	DESCRIPTION
	    "Total number of 'no route found' error in life time."
	::= {apDdErrorStatusEntry 2}

apDdNoRouteFoundPerMax	OBJECT-TYPE
	SYNTAX		Counter32
	MAX-ACCESS 	read-only
	STATUS		current
	DESCRIPTION
	    "Maximum value of apDdNoRouteFoundRecent across all periods (high water mark)."
	::= {apDdErrorStatusEntry 3}

apDdMalformedMsgRecent	OBJECT-TYPE
	SYNTAX		Gauge32
	MAX-ACCESS 	read-only
	STATUS		current
	DESCRIPTION
	    "Number of 'mal-formed message' error in recent period."
	::= {apDdErrorStatusEntry 4}

apDdMalformedMsgTotal	OBJECT-TYPE
	SYNTAX		Counter32
	MAX-ACCESS 	read-only
	STATUS		current
	DESCRIPTION
	    "Total number of 'mal-formed message' error in life time."
	::= {apDdErrorStatusEntry 5}

apDdMalformedMsgPerMax	OBJECT-TYPE
	SYNTAX		Counter32
	MAX-ACCESS 	read-only
	STATUS		current
	DESCRIPTION
	    "Maximum value of apDdMalformedMsgRecent across all periods (high water mark)."
	::= {apDdErrorStatusEntry 6}


apDdRejectedMsgRecent	OBJECT-TYPE
	SYNTAX		Gauge32
	MAX-ACCESS 	read-only
	STATUS		current
	DESCRIPTION
	    "Number of 'rejected msg'' error in recent period."
	::= {apDdErrorStatusEntry 7}

apDdRejectedMsgTotal	OBJECT-TYPE
	SYNTAX		Counter32
	MAX-ACCESS 	read-only
	STATUS		current
	DESCRIPTION
	    "Total number of 'rejected msg' error in life time."
	::= {apDdErrorStatusEntry 8}

apDdRejectedMsgPerMax	OBJECT-TYPE
	SYNTAX		Counter32
	MAX-ACCESS 	read-only
	STATUS		current
	DESCRIPTION
	    "Maximum value of apDdRejectedMsgRecent across all periods (high water mark)."
	::= {apDdErrorStatusEntry 9}

apDdDroppedMsgRecent	OBJECT-TYPE
	SYNTAX		Gauge32
	MAX-ACCESS 	read-only
	STATUS		current
	DESCRIPTION
	    "Number of 'dropped msg'' error in recent period."
	::= {apDdErrorStatusEntry 10}

apDdDroppedMsgTotal	OBJECT-TYPE
	SYNTAX		Counter32
	MAX-ACCESS 	read-only
	STATUS		current
	DESCRIPTION
	    "Total number of 'dropped msg' error in life time."
	::= {apDdErrorStatusEntry 11}

apDdDroppedMsgPerMax	OBJECT-TYPE
	SYNTAX		Counter32
	MAX-ACCESS 	read-only
	STATUS		current
	DESCRIPTION
	    "Maximum value of apDdDroppedMsgRecent across all periods (high water mark)."
	::= {apDdErrorStatusEntry 12}

apDdInboundConstraintsRecent	OBJECT-TYPE
	SYNTAX		Gauge32
	MAX-ACCESS 	read-only
	STATUS		current
	DESCRIPTION
	    "Number of 'inbound constraints'' error in recent period."
	::= {apDdErrorStatusEntry 13}

apDdInboundConstraintsTotal	OBJECT-TYPE
	SYNTAX		Counter32
	MAX-ACCESS 	read-only
	STATUS		current
	DESCRIPTION
	    "Total number of 'inbound constraints' error in life time."
	::= {apDdErrorStatusEntry 14}

apDdInboundConstraintsPerMax	OBJECT-TYPE
	SYNTAX		Counter32
	MAX-ACCESS 	read-only
	STATUS		current
	DESCRIPTION
	    "Maximum value of apDdInboundConstraintsRecent across all periods (high water mark)."
	::= {apDdErrorStatusEntry 15}

apDdOutboundConstraintsRecent	OBJECT-TYPE
	SYNTAX		Gauge32
	MAX-ACCESS 	read-only
	STATUS		current
	DESCRIPTION
	    "Number of 'outbound constraints'' error in recent period."
	::= {apDdErrorStatusEntry 16}

apDdOutboundConstraintsTotal	OBJECT-TYPE
	SYNTAX		Counter32
	MAX-ACCESS 	read-only
	STATUS		current
	DESCRIPTION
	    "Total number of 'outbound constraints' error in life time."
	::= {apDdErrorStatusEntry 17}

apDdOutboundConstraintsPerMax	OBJECT-TYPE
	SYNTAX		Counter32
	MAX-ACCESS 	read-only
	STATUS		current
	DESCRIPTION
	    "Maximum value of apDdOutboundConstraintsRecent across all periods (high water mark)."
	::= {apDdErrorStatusEntry 18}


apDdMsgTypeInfoTable       	OBJECT-TYPE
        SYNTAX          SEQUENCE OF ApDdMsgTypeInfoEntry
        MAX-ACCESS      not-accessible
        STATUS          current
        DESCRIPTION
	    "static system message type information."
        ::= { apDDMIBTabularObjects 3 }

apDdMsgTypeInfoEntry         OBJECT-TYPE
        SYNTAX          ApDdMsgTypeInfoEntry
        MAX-ACCESS      not-accessible
        STATUS          current
        DESCRIPTION
	    "A table entry designed for message type inf."
        INDEX { apDdMsgTypeIndex }
        ::= { apDdMsgTypeInfoTable 1 }

ApDdMsgTypeInfoEntry ::= SEQUENCE {
        apDdMsgTypeIndex                              INTEGER,
        apDdMsgTypeMsgName                            DisplayString
	}

apDdMsgTypeIndex		OBJECT-TYPE
        SYNTAX			INTEGER (1..2147483647)
        MAX-ACCESS		not-accessible
        STATUS			current
        DESCRIPTION
	    "An integer for the sole purpose of indexing DD message types."
	::= {apDdMsgTypeInfoEntry 1}

apDdMsgTypeMsgName		OBJECT-TYPE
	SYNTAX 			DisplayString (SIZE (0..255))
	MAX-ACCESS		read-only
	STATUS			current
	DESCRIPTION
	    "The identification string of the message type."
	::= {apDdMsgTypeInfoEntry 2}

apDdMsgTypeStatsTable       	OBJECT-TYPE
        SYNTAX          SEQUENCE OF ApDdMsgTypeStatsEntry
        MAX-ACCESS      not-accessible
        STATUS          current
        DESCRIPTION
	    "table for holding message type stats."
        ::= { apDDMIBTabularObjects 4 }

apDdMsgTypeStatsEntry         OBJECT-TYPE
        SYNTAX          ApDdMsgTypeStatsEntry
        MAX-ACCESS      not-accessible
        STATUS          current
        DESCRIPTION
	    "A table entry designed for message type statistics."
        INDEX { apDdInterfaceIndex, apDdMsgTypeIndex }
        ::= { apDdMsgTypeStatsTable 1 }

ApDdMsgTypeStatsEntry ::= SEQUENCE {
        apDdMsgTypeServerReqRecent                    Gauge32,
        apDdMsgTypeServerReqTotal                     Counter32,
        apDdMsgTypeServerReqPerMax                    Counter32,
        apDdMsgTypeClientReqRecent                    Gauge32,
        apDdMsgTypeClientReqTotal                     Counter32,
        apDdMsgTypeClientReqPerMax                    Counter32,
        apDdMsgTypeServerRetransRecent                    Gauge32,
        apDdMsgTypeServerRetransTotal                     Counter32,
        apDdMsgTypeServerRetransPerMax                    Counter32,
        apDdMsgTypeClientRetransRecent                    Gauge32,
        apDdMsgTypeClientRetransTotal                     Counter32,
        apDdMsgTypeClientRetransPerMax                    Counter32,
        apDdMsgTypeServerRespRetransRecent                 Gauge32,
        apDdMsgTypeServerRespRetransTotal                  Counter32,
        apDdMsgTypeServerRespRetransPerMax                 Counter32,
        apDdMsgTypeClientRespRetransRecent                 Gauge32,
        apDdMsgTypeClientRespRetransTotal                  Counter32,
        apDdMsgTypeClientRespRetransPerMax                 Counter32,
        apDdMsgTypeClientTimeoutRecent                Gauge32,
        apDdMsgTypeClientTimeoutTotal                 Counter32,
        apDdMsgTypeClientTimeoutPerMax                Counter32,
        apDdMsgTypeClientThrottledRecent              Gauge32,
        apDdMsgTypeClientThrottledTotal               Counter32,
        apDdMsgTypeClientThrottledPerMax              Counter32,
        apDdMsgTypeAverageLatency                     Gauge32,
        apDdMsgTypeMaximumLatency                     Gauge32,
        apDdMsgTypeLatencyWindow                      Integer32
}

apDdMsgTypeServerReqRecent	OBJECT-TYPE
	SYNTAX			Gauge32
	MAX-ACCESS 		read-only
	STATUS			current
	DESCRIPTION
	    "Number of server requests in recent period."
	::= {apDdMsgTypeStatsEntry 3}

apDdMsgTypeServerReqTotal	OBJECT-TYPE
	SYNTAX			Counter32
	MAX-ACCESS 		read-only
	STATUS			current
	DESCRIPTION
	    "Total number of server requests in life time."
	::= {apDdMsgTypeStatsEntry 4}

apDdMsgTypeServerReqPerMax	OBJECT-TYPE
	SYNTAX			Counter32
	MAX-ACCESS 		read-only
	STATUS			current
	DESCRIPTION
	    "Maximum value of apDdMsgTypeServerReqRecent across all periods (high water mark)"
	::= {apDdMsgTypeStatsEntry 5}

apDdMsgTypeClientReqRecent	OBJECT-TYPE
	SYNTAX			Gauge32
	MAX-ACCESS 		read-only
	STATUS			current
	DESCRIPTION
	    "Number of client requests in recent period."
	::= {apDdMsgTypeStatsEntry 6}

apDdMsgTypeClientReqTotal	OBJECT-TYPE
	SYNTAX			Counter32
	MAX-ACCESS 		read-only
	STATUS			current
	DESCRIPTION
	    "Total number of client requests in life time."
	::= {apDdMsgTypeStatsEntry 7}

apDdMsgTypeClientReqPerMax	OBJECT-TYPE
	SYNTAX			Counter32
	MAX-ACCESS 		read-only
	STATUS			current
	DESCRIPTION
	    "Maximum value of apDdMsgTypeClientReqRecent across all periods (high water mark)."
	::= {apDdMsgTypeStatsEntry 8}

apDdMsgTypeServerRetransRecent	OBJECT-TYPE
	SYNTAX			Gauge32
	MAX-ACCESS 		read-only
	STATUS			current
	DESCRIPTION
	    "Number of server retransmissions in recent period."
	::= {apDdMsgTypeStatsEntry 9}

apDdMsgTypeServerRetransTotal	OBJECT-TYPE
	SYNTAX			Counter32
	MAX-ACCESS 		read-only
	STATUS			current
	DESCRIPTION
	    "Total number of server retransmissions in life time."
	::= {apDdMsgTypeStatsEntry 10}

apDdMsgTypeServerRetransPerMax	OBJECT-TYPE
	SYNTAX			Counter32
	MAX-ACCESS 		read-only
	STATUS			current
	DESCRIPTION
	    "Maximum value of apDdMsgTypeServerRetransRecent across all periods (high water mark)"
	::= {apDdMsgTypeStatsEntry 11}

apDdMsgTypeClientRetransRecent	OBJECT-TYPE
	SYNTAX			Gauge32
	MAX-ACCESS 		read-only
	STATUS			current
	DESCRIPTION
	    "Number of client retransmissions in recent period."
	::= {apDdMsgTypeStatsEntry 12}

apDdMsgTypeClientRetransTotal	OBJECT-TYPE
	SYNTAX			Counter32
	MAX-ACCESS 		read-only
	STATUS			current
	DESCRIPTION
	    "Total number of client retransmissions in life time."
	::= {apDdMsgTypeStatsEntry 13}

apDdMsgTypeClientRetransPerMax	OBJECT-TYPE
	SYNTAX			Counter32
	MAX-ACCESS 		read-only
	STATUS			current
	DESCRIPTION
	    "Maximum value of apDdMsgTypeClientRetransRecent across all periods (high water mark)."
	::= {apDdMsgTypeStatsEntry 14}

apDdMsgTypeServerRespRetransRecent	OBJECT-TYPE
	SYNTAX			Gauge32
	MAX-ACCESS 		read-only
	STATUS			current
	DESCRIPTION
	    "Number of server response retransactions in recent period."
	::= {apDdMsgTypeStatsEntry 15}

apDdMsgTypeServerRespRetransTotal	OBJECT-TYPE
	SYNTAX			Counter32
	MAX-ACCESS 		read-only
	STATUS			current
	DESCRIPTION
	    "Total number of server response retransactions in life time."
	::= {apDdMsgTypeStatsEntry 16}

apDdMsgTypeServerRespRetransPerMax	OBJECT-TYPE
	SYNTAX			Counter32
	MAX-ACCESS 		read-only
	STATUS			current
	DESCRIPTION
	    "Maximum value of apDdMsgTypeServerRespRetransRecent across all periods (high water mark)."
	::= {apDdMsgTypeStatsEntry 17}

apDdMsgTypeClientRespRetransRecent	OBJECT-TYPE
	SYNTAX			Gauge32
	MAX-ACCESS 		read-only
	STATUS			current
	DESCRIPTION
	    "Number of client response retransactions in recent period."
	::= {apDdMsgTypeStatsEntry 21}

apDdMsgTypeClientRespRetransTotal	OBJECT-TYPE
	SYNTAX			Counter32
	MAX-ACCESS 		read-only
	STATUS			current
	DESCRIPTION
	    "Total number of client response retransactions in life time."
	::= {apDdMsgTypeStatsEntry 22}

apDdMsgTypeClientRespRetransPerMax	OBJECT-TYPE
	SYNTAX			Counter32
	MAX-ACCESS 		read-only
	STATUS			current
	DESCRIPTION
	    "Maximum value of apDdMsgTypeClientRespRetransRecent across all periods (high water mark)."
	::= {apDdMsgTypeStatsEntry 23}

apDdMsgTypeClientTimeoutRecent	OBJECT-TYPE
	SYNTAX			Gauge32
	MAX-ACCESS 		read-only
	STATUS			current
	DESCRIPTION
	    "Number of client transaction timeout in recent period."
	::= {apDdMsgTypeStatsEntry 27}

apDdMsgTypeClientTimeoutTotal	OBJECT-TYPE
	SYNTAX			Counter32
	MAX-ACCESS 		read-only
	STATUS			current
	DESCRIPTION
	    "Total number of client transaction timeout in life time."
	::= {apDdMsgTypeStatsEntry 28}

apDdMsgTypeClientTimeoutPerMax	OBJECT-TYPE
	SYNTAX			Counter32
	MAX-ACCESS 		read-only
	STATUS			current
	DESCRIPTION
	    "Maximum value of apDdMsgTypeClientTimeoutRecent across all periods (high water mark)."
	::= {apDdMsgTypeStatsEntry 29}

apDdMsgTypeClientThrottledRecent	OBJECT-TYPE
	SYNTAX			Gauge32
	MAX-ACCESS 		read-only
	STATUS			current
	DESCRIPTION
	    "Number of locally throttled client count in recent period."
	::= {apDdMsgTypeStatsEntry 33}

apDdMsgTypeClientThrottledTotal	OBJECT-TYPE
	SYNTAX			Counter32
	MAX-ACCESS 		read-only
	STATUS			current
	DESCRIPTION
	    "Total number of locally throttled client count in life time."
	::= {apDdMsgTypeStatsEntry 34}

apDdMsgTypeClientThrottledPerMax	OBJECT-TYPE
	SYNTAX			Counter32
	MAX-ACCESS 		read-only
	STATUS			current
	DESCRIPTION
	    "Maximum value of apDdMsgTypeClientThrottledRecent across all periods (high water mark)."
	::= {apDdMsgTypeStatsEntry 35}

apDdMsgTypeAverageLatency	OBJECT-TYPE
	SYNTAX			Gauge32
	MAX-ACCESS 		read-only
	STATUS			current
	DESCRIPTION
	    "Average Latency."
	::= {apDdMsgTypeStatsEntry 36}

apDdMsgTypeMaximumLatency	OBJECT-TYPE
	SYNTAX			Gauge32
	MAX-ACCESS 		read-only
	STATUS			current
	DESCRIPTION
	    "Maximum Latency."
	::= {apDdMsgTypeStatsEntry 37}

apDdMsgTypeLatencyWindow	OBJECT-TYPE
	SYNTAX			Integer32
	UNITS			"second"
	MAX-ACCESS 		read-only
	STATUS			current
	DESCRIPTION
	    "Latency window length."
	::= {apDdMsgTypeStatsEntry 38}

apDdMsgReturnCodeInfoTable       	OBJECT-TYPE
        SYNTAX          SEQUENCE OF ApDdMsgReturnCodeInfoEntry
        MAX-ACCESS      not-accessible
        STATUS          current
        DESCRIPTION
	    "DD return message code stats table."
        ::= { apDDMIBTabularObjects 5 }

apDdMsgReturnCodeInfoEntry         OBJECT-TYPE
        SYNTAX          ApDdMsgReturnCodeInfoEntry
        MAX-ACCESS      not-accessible
        STATUS          current
        DESCRIPTION
	    "A table entry designed to hold return code stats."
        INDEX { apDdMsgReturnCodeIndex }
        ::= { apDdMsgReturnCodeInfoTable 1 }

ApDdMsgReturnCodeInfoEntry ::= SEQUENCE {
        apDdMsgReturnCodeIndex                        INTEGER,
        apDdMsgReturnCodeName                         DisplayString
}

apDdMsgReturnCodeIndex		OBJECT-TYPE
        SYNTAX			INTEGER (1..2147483647)
        MAX-ACCESS		not-accessible
        STATUS			current
        DESCRIPTION
	    "An integer for the sole purpose of indexing message return code."
	::= {apDdMsgReturnCodeInfoEntry 1}

apDdMsgReturnCodeName		OBJECT-TYPE
	SYNTAX 			DisplayString (SIZE (0..255))
	MAX-ACCESS		read-only
	STATUS			current
	DESCRIPTION
	    "The name string of the message return code."
	::= {apDdMsgReturnCodeInfoEntry 2}

apDdMsgStatsReturnCodeTable       	OBJECT-TYPE
        SYNTAX          SEQUENCE OF ApDdMsgStatsReturnCodeEntry
        MAX-ACCESS      not-accessible
        STATUS          current
        DESCRIPTION
	    "DD return message code stats table."
        ::= { apDDMIBTabularObjects 6 }

apDdMsgStatsReturnCodeEntry         OBJECT-TYPE
        SYNTAX          ApDdMsgStatsReturnCodeEntry
        MAX-ACCESS      not-accessible
        STATUS          current
        DESCRIPTION
	    "A table entry designed to hold return code stats."
        INDEX 
	{ apDdInterfaceIndex, apDdMsgTypeIndex, apDdMsgReturnCodeIndex }
        ::= { apDdMsgStatsReturnCodeTable 1 }

ApDdMsgStatsReturnCodeEntry ::= SEQUENCE {
        apDdMsgReturnCodeServerRecent                 Gauge32,
        apDdMsgReturnCodeServerTotal                  Counter32,
        apDdMsgReturnCodeServerPerMax                 Counter32,
        apDdMsgReturnCodeClientRecent                 Gauge32,
        apDdMsgReturnCodeClientTotal                  Counter32,
        apDdMsgReturnCodeClientPerMax                 Counter32
}

apDdMsgReturnCodeServerRecent	OBJECT-TYPE
	SYNTAX			Gauge32
	MAX-ACCESS 		read-only
	STATUS			current
	DESCRIPTION
	    "Number of server requests in recent period."
	::= {apDdMsgStatsReturnCodeEntry 3}

apDdMsgReturnCodeServerTotal	OBJECT-TYPE
	SYNTAX			Counter32
	MAX-ACCESS 		read-only
	STATUS			current
	DESCRIPTION
	    "Total number of server requests in life time."
	::= {apDdMsgStatsReturnCodeEntry 4}

apDdMsgReturnCodeServerPerMax	OBJECT-TYPE
	SYNTAX			Counter32
	MAX-ACCESS 		read-only
	STATUS			current
	DESCRIPTION
	    "Maximum value of apDdMsgReturnCodeServerRecent across all periods (high water mark)."
	::= {apDdMsgStatsReturnCodeEntry 5}

apDdMsgReturnCodeClientRecent	OBJECT-TYPE
	SYNTAX			Gauge32
	MAX-ACCESS 		read-only
	STATUS			current
	DESCRIPTION
	    "Number of server requests in recent period."
	::= {apDdMsgStatsReturnCodeEntry 6}

apDdMsgReturnCodeClientTotal	OBJECT-TYPE
	SYNTAX			Counter32
	MAX-ACCESS 		read-only
	STATUS			current
	DESCRIPTION
	    "Total number of server requests in life time."
	::= {apDdMsgStatsReturnCodeEntry 7}

apDdMsgReturnCodeClientPerMax	OBJECT-TYPE
	SYNTAX			Counter32
	MAX-ACCESS 		read-only
	STATUS			current
	DESCRIPTION
	    "Maximum value of apDdMsgReturnCodeClientRecent across all periods (high water mark)."
	::= {apDdMsgStatsReturnCodeEntry 8}


apDdDnsStatsTable       	OBJECT-TYPE
        SYNTAX          SEQUENCE OF ApDdDnsStatsEntry
        MAX-ACCESS      not-accessible
        STATUS          current
        DESCRIPTION
	    "per DD interface dns stats."
        ::= { apDDMIBTabularObjects 11 }

apDdDnsStatsEntry         OBJECT-TYPE
        SYNTAX          ApDdDnsStatsEntry
        MAX-ACCESS      not-accessible
        STATUS          current
        DESCRIPTION
	    "A table entry designed to hold dns stats data"
        INDEX { apDdInterfaceIndex }
        ::= { apDdDnsStatsTable 1 }

ApDdDnsStatsEntry ::= SEQUENCE {
        apDdDnsQueriesRecent                    Gauge32,
        apDdDnsQueriesTotal                     Counter32,
        apDdDnsQueriesPerMax                    Counter32,
        apDdDnsCacheHitsRecent                  Gauge32,
        apDdDnsCacheHitsTotal                   Counter32,
        apDdDnsCacheHitsPerMax                  Counter32,
        apDdDnsCacheMissesRecent                Gauge32,
        apDdDnsCacheMissesTotal                 Counter32,
        apDdDnsCacheMissesPerMax                Counter32,
        apDdDnsClientErrorsRecent               Gauge32,
        apDdDnsClientErrorsTotal                Counter32,
        apDdDnsClientErrorsPerMax               Counter32,
        apDdDnsServerErrorsRecent               Gauge32,
        apDdDnsServerErrorsTotal                Counter32,
        apDdDnsServerErrorsPerMax               Counter32,
        apDdDnsResponsesRecent                  Gauge32,
        apDdDnsResponsesTotal                   Counter32,
        apDdDnsResponsesPerMax                  Counter32
}
apDdDnsQueriesRecent	OBJECT-TYPE
	SYNTAX		Gauge32
	MAX-ACCESS 	read-only
	STATUS		current
	DESCRIPTION
	    "Number of dns queries in recent period."
	::= {apDdDnsStatsEntry 1}

apDdDnsQueriesTotal	    OBJECT-TYPE
	SYNTAX		Counter32
	MAX-ACCESS 	read-only
	STATUS		current
	DESCRIPTION
	    "Number of dns queries in total period."
	::= {apDdDnsStatsEntry 2}


apDdDnsQueriesPerMax	OBJECT-TYPE
	SYNTAX		Counter32
	MAX-ACCESS 	read-only
	STATUS		current
	DESCRIPTION
	    "Maximum value of apDdDnsQueriesRecent across all periods (high water mark)."
	::= {apDdDnsStatsEntry 3}

apDdDnsCacheHitsRecent	OBJECT-TYPE
	SYNTAX		Gauge32
	MAX-ACCESS 	read-only
	STATUS		current
	DESCRIPTION
	    "Number of dns cache hits in recent period."
	::= {apDdDnsStatsEntry 4}

apDdDnsCacheHitsTotal	    OBJECT-TYPE
	SYNTAX		Counter32
	MAX-ACCESS 	read-only
	STATUS		current
	DESCRIPTION
	    "Number of dns cache hits in total period."
	::= {apDdDnsStatsEntry 5}


apDdDnsCacheHitsPerMax	OBJECT-TYPE
	SYNTAX		Counter32
	MAX-ACCESS 	read-only
	STATUS		current
	DESCRIPTION
	    "Maximum value of apDdDnsCacheHitsRecent across all periods (high water mark)."
	::= {apDdDnsStatsEntry 6}

apDdDnsCacheMissesRecent	OBJECT-TYPE
	SYNTAX		Gauge32
	MAX-ACCESS 	read-only
	STATUS		current
	DESCRIPTION
	    "Number of dns cache misses in recent period."
	::= {apDdDnsStatsEntry 7}

apDdDnsCacheMissesTotal	    OBJECT-TYPE
	SYNTAX		Counter32
	MAX-ACCESS 	read-only
	STATUS		current
	DESCRIPTION
	    "Number of dns cache misses in total period."
	::= {apDdDnsStatsEntry 8}


apDdDnsCacheMissesPerMax	OBJECT-TYPE
	SYNTAX		Counter32
	MAX-ACCESS 	read-only
	STATUS		current
	DESCRIPTION
	    "Maximum value of apDdDnsCacheMissesRecent across all periods (high water mark)."
	::= {apDdDnsStatsEntry 9}	
	
apDdDnsClientErrorsRecent	OBJECT-TYPE
	SYNTAX		Gauge32
	MAX-ACCESS 	read-only
	STATUS		current
	DESCRIPTION
	    "Number of dns client errors in recent period."
	::= {apDdDnsStatsEntry 10}

apDdDnsClientErrorsTotal	    OBJECT-TYPE
	SYNTAX		Counter32
	MAX-ACCESS 	read-only
	STATUS		current
	DESCRIPTION
	    "Number of dns client errors in total period."
	::= {apDdDnsStatsEntry 11}


apDdDnsClientErrorsPerMax	OBJECT-TYPE
	SYNTAX		Counter32
	MAX-ACCESS 	read-only
	STATUS		current
	DESCRIPTION
	    "Maximum value of apDdDnsClientErrorsRecent across all periods (high water mark)."
	::= {apDdDnsStatsEntry 12}
		
apDdDnsServerErrorsRecent	OBJECT-TYPE
	SYNTAX		Gauge32
	MAX-ACCESS 	read-only
	STATUS		current
	DESCRIPTION
	    "Number of dns server errors in recent period."
	::= {apDdDnsStatsEntry 13}

apDdDnsServerErrorsTotal	    OBJECT-TYPE
	SYNTAX		Counter32
	MAX-ACCESS 	read-only
	STATUS		current
	DESCRIPTION
	    "Number of dns server errors in total period."
	::= {apDdDnsStatsEntry 14}


apDdDnsServerErrorsPerMax	OBJECT-TYPE
	SYNTAX		Counter32
	MAX-ACCESS 	read-only
	STATUS		current
	DESCRIPTION
	    "Maximum value of apDdDnsServerErrorsRecent across all periods (high water mark)."
	::= {apDdDnsStatsEntry 15}	
		
apDdDnsResponsesRecent	OBJECT-TYPE
	SYNTAX		Gauge32
	MAX-ACCESS 	read-only
	STATUS		current
	DESCRIPTION
	    "Number of dns responses in recent period."
	::= {apDdDnsStatsEntry 16}

apDdDnsResponsesTotal	    OBJECT-TYPE
	SYNTAX		Counter32
	MAX-ACCESS 	read-only
	STATUS		current
	DESCRIPTION
	    "Number of dns responses in total period."
	::= {apDdDnsStatsEntry 17}


apDdDnsResponsesPerMax	OBJECT-TYPE
	SYNTAX		Counter32
	MAX-ACCESS 	read-only
	STATUS		current
	DESCRIPTION
	    "Maximum value of apDdDnsResponsesRecent across all periods (high water mark)."
	::= {apDdDnsStatsEntry 18}	






-- End of Interface Tabular Object

-- Start of Agent Tabular Object


apDdAgentStatsTable       	OBJECT-TYPE
        SYNTAX          SEQUENCE OF ApDdAgentStatsEntry
        MAX-ACCESS      not-accessible
        STATUS          current
        DESCRIPTION
	    "DD agent statistics."
        ::= { apDDMIBTabularObjects 7}

apDdAgentStatsEntry         OBJECT-TYPE
        SYNTAX          ApDdAgentStatsEntry
        MAX-ACCESS      not-accessible
        STATUS          current
        DESCRIPTION
	    "A table entry designed to hold per DD agent statistics."
        INDEX { apDdAgentIndex }
        ::= { apDdAgentStatsTable 1 }

ApDdAgentStatsEntry ::= SEQUENCE {
        apDdAgentIndex           		INTEGER,
        apDdAgentRealmName		        DisplayString,
        apDdAgentClientTransCPActive                Gauge32,
        apDdAgentClientTransCPHigh                  Counter32,
        apDdAgentClientTransCPTotal                 Counter32,
        apDdAgentClientTransLTTotal                 Counter32,
        apDdAgentClientTransLTPerMax                Counter32,
        apDdAgentClientTransLTHigh                  Counter32,
        apDdAgentServerTransCPActive                Gauge32,
        apDdAgentServerTransCPHigh                  Counter32,
        apDdAgentServerTransCPTotal                 Counter32,
        apDdAgentServerTransLTTotal                 Counter32,
        apDdAgentServerTransLTPerMax                Counter32,
        apDdAgentServerTransLTHigh                  Counter32,
        apDdAgentGenSocketsCPActive                 Gauge32,
        apDdAgentGenSocketsCPHigh                   Counter32,
        apDdAgentGenSocketsCPTotal                  Counter32,
        apDdAgentGenSocketsLTTotal                  Counter32,
        apDdAgentGenSocketsLTPerMax                 Counter32,
        apDdAgentGenSocketsLTHigh                   Counter32,
        apDdAgentGenConnectsCPActive                Gauge32,
        apDdAgentGenConnectsCPHigh                  Counter32,
        apDdAgentGenConnectsCPTotal                 Counter32,
        apDdAgentGenConnectsLTTotal                 Counter32,
        apDdAgentGenConnectsLTPerMax                Counter32,
        apDdAgentGenConnectsLTHigh                  Counter32,
        apDdAgentStatus                             ApDdStatusOptions
}

apDdAgentIndex		OBJECT-TYPE
        SYNTAX			INTEGER (1..2147483647)
        MAX-ACCESS		accessible-for-notify
        STATUS			current
        DESCRIPTION
	    "An integer for the sole purpose of indexing the DD agent."
	::= {apDdAgentStatsEntry 1}

apDdAgentRealmName		OBJECT-TYPE
	SYNTAX 			DisplayString (SIZE (0..255))
	MAX-ACCESS		read-only
	STATUS			current
	DESCRIPTION
	    "Realm name of the DD agent if the row is for per agent 
	    stats. Otherwise, it is an empty string."
	::= {apDdAgentStatsEntry 2}

apDdAgentClientTransCPActive	OBJECT-TYPE
	SYNTAX		Gauge32
	MAX-ACCESS 	read-only
	STATUS		current
	DESCRIPTION
	    "Number of active client transactions in the current period."
	::= {apDdAgentStatsEntry 3}

apDdAgentClientTransCPHigh	OBJECT-TYPE
	SYNTAX		Counter32
	MAX-ACCESS 	read-only
	STATUS		current
	DESCRIPTION
	    "Maximum value of apDdAgentClientTransCPActive in the current period (high water mark).  "
	::= {apDdAgentStatsEntry 4}

apDdAgentClientTransCPTotal	OBJECT-TYPE
	SYNTAX		Counter32
	MAX-ACCESS 	read-only
	STATUS		current
	DESCRIPTION
	    "Total number of client transactions in the current period."
	::= {apDdAgentStatsEntry 5}

apDdAgentClientTransLTTotal	OBJECT-TYPE
	SYNTAX		Counter32
	MAX-ACCESS 	read-only
	STATUS		current
	DESCRIPTION
	    "Total number of transactions in client side in life time."
	::= {apDdAgentStatsEntry 6}

apDdAgentClientTransLTPerMax	OBJECT-TYPE
	SYNTAX		Counter32
	MAX-ACCESS 	read-only
	STATUS		current
	DESCRIPTION
	    "Maximum value of apDdAgentClientTransCPTotal across all periods (high water mark)."
	::= {apDdAgentStatsEntry 7}

apDdAgentClientTransLTHigh	OBJECT-TYPE
	SYNTAX		Counter32
	MAX-ACCESS 	read-only
	STATUS		current
	DESCRIPTION
	    "Maximum value of apDdAgentClientTransCPHigh across all periods (high water mark)."
	::= {apDdAgentStatsEntry 8}

apDdAgentServerTransCPActive	OBJECT-TYPE
	SYNTAX		Gauge32
	MAX-ACCESS 	read-only
	STATUS		current
	DESCRIPTION
	    "Number of active transactions in server side in current period."
	::= {apDdAgentStatsEntry 9}

apDdAgentServerTransCPHigh	OBJECT-TYPE
	SYNTAX		Counter32
	MAX-ACCESS 	read-only
	STATUS		current
	DESCRIPTION
	    "Highest number of active transactions in server side in current period."
	::= {apDdAgentStatsEntry 10}

apDdAgentServerTransCPTotal	OBJECT-TYPE
	SYNTAX		Counter32
	MAX-ACCESS 	read-only
	STATUS		current
	DESCRIPTION
	    "Total number of transactions in server side in current period."
	::= {apDdAgentStatsEntry 11}

apDdAgentServerTransLTTotal	OBJECT-TYPE
	SYNTAX		Counter32
	MAX-ACCESS 	read-only
	STATUS		current
	DESCRIPTION
	    "Total number of transactions in server side in life time."
	::= {apDdAgentStatsEntry 12}

apDdAgentServerTransLTPerMax	OBJECT-TYPE
	SYNTAX		Counter32
	MAX-ACCESS 	read-only
	STATUS		current
	DESCRIPTION
	    "Maximum value of apDdAgentServerTransCPTotal across all periods (high water mark)."
	::= {apDdAgentStatsEntry 13}

apDdAgentServerTransLTHigh	OBJECT-TYPE
	SYNTAX		Counter32
	MAX-ACCESS 	read-only
	STATUS		current
	DESCRIPTION
	    "Maximum value of apDdAgentServerTransCPHigh across all periods (high water mark)."
	::= {apDdAgentStatsEntry 14}

apDdAgentGenSocketsCPActive	OBJECT-TYPE
	SYNTAX		Gauge32
	MAX-ACCESS 	read-only
	STATUS		current
	DESCRIPTION
	    "Number of active sockets in current period."
	::= {apDdAgentStatsEntry 15}

apDdAgentGenSocketsCPHigh	OBJECT-TYPE
	SYNTAX		Counter32
	MAX-ACCESS 	read-only
	STATUS		current
	DESCRIPTION
	    "Highest number of active sockets in current period."
	::= {apDdAgentStatsEntry 16}

apDdAgentGenSocketsCPTotal	OBJECT-TYPE
	SYNTAX		Counter32
	MAX-ACCESS 	read-only
	STATUS		current
	DESCRIPTION
	    "Total number of sockets in current period."
	::= {apDdAgentStatsEntry 17}

apDdAgentGenSocketsLTTotal	OBJECT-TYPE
	SYNTAX		Counter32
	MAX-ACCESS 	read-only
	STATUS		current
	DESCRIPTION
	    "Total number of sockets in life time."
	::= {apDdAgentStatsEntry 18}

apDdAgentGenSocketsLTPerMax	OBJECT-TYPE
	SYNTAX		Counter32
	MAX-ACCESS 	read-only
	STATUS		current
	DESCRIPTION
	    "Maximum value of apDdAgentSocketsCPTotal across all periods (high water mark)."
	::= {apDdAgentStatsEntry 19}

apDdAgentGenSocketsLTHigh	OBJECT-TYPE
	SYNTAX		Counter32
	MAX-ACCESS 	read-only
	STATUS		current
	DESCRIPTION
	    "Maximum value of apDdAgentSocketsCPHigh across all periods (high water mark)."
	::= {apDdAgentStatsEntry 20}

apDdAgentGenConnectsCPActive	OBJECT-TYPE
	SYNTAX		Gauge32
	MAX-ACCESS 	read-only
	STATUS		current
	DESCRIPTION
	    "Number of active connections in current period."
	::= {apDdAgentStatsEntry 21}

apDdAgentGenConnectsCPHigh	OBJECT-TYPE
	SYNTAX		Counter32
	MAX-ACCESS 	read-only
	STATUS		current
	DESCRIPTION
	    "high number of connections in current period."
	::= {apDdAgentStatsEntry 22}

apDdAgentGenConnectsCPTotal	OBJECT-TYPE
	SYNTAX		Counter32
	MAX-ACCESS 	read-only
	STATUS		current
	DESCRIPTION
	    "Total number of connections in current period."
	::= {apDdAgentStatsEntry 23}

apDdAgentGenConnectsLTTotal	OBJECT-TYPE
	SYNTAX		Counter32
	MAX-ACCESS 	read-only
	STATUS		current
	DESCRIPTION
	    "Total number of connections in life time."
	::= {apDdAgentStatsEntry 24}

apDdAgentGenConnectsLTPerMax	OBJECT-TYPE
	SYNTAX		Counter32
	MAX-ACCESS 	read-only
	STATUS		current
	DESCRIPTION
	    "Maximum value of apDdConnectsCPTotal across all periods (high water mark)."
	::= {apDdAgentStatsEntry 25}

apDdAgentGenConnectsLTHigh	OBJECT-TYPE
	SYNTAX		Counter32
	MAX-ACCESS 	read-only
	STATUS		current
	DESCRIPTION
	    "Maximum value of apDdAgentConnectsCPHigh across all periods (high water mark)."
	::= {apDdAgentStatsEntry 26}

apDdAgentStatus			OBJECT-TYPE
	SYNTAX		ApDdStatusOptions
	MAX-ACCESS	read-only
	STATUS		current
	DESCRIPTION
	    "Status of the DD Agents in the system."
	::= {apDdAgentStatsEntry 27}

apDdAgentErrorStatusTable       	OBJECT-TYPE
        SYNTAX          SEQUENCE OF ApDdAgentErrorStatusEntry
        MAX-ACCESS      not-accessible
        STATUS          current
        DESCRIPTION
	    "per DD agent error stats."
        ::= { apDDMIBTabularObjects 8 }

apDdAgentErrorStatusEntry         OBJECT-TYPE
        SYNTAX          ApDdAgentErrorStatusEntry
        MAX-ACCESS      not-accessible
        STATUS          current
        DESCRIPTION
	    "A table entry designed to hold error status data"
        INDEX { apDdAgentIndex }
        ::= { apDdAgentErrorStatusTable 1 }

ApDdAgentErrorStatusEntry ::= SEQUENCE {
        apDdAgentNoRouteFoundRecent                        Gauge32,
        apDdAgentNoRouteFoundTotal                         Counter32,
        apDdAgentNoRouteFoundPerMax                        Counter32,
        apDdAgentMalformedMsgRecent                        Gauge32,
        apDdAgentMalformedMsgTotal                         Counter32,
        apDdAgentMalformedMsgPerMax                        Counter32,
        apDdAgentRejectedMsgRecent                         Gauge32,
        apDdAgentRejectedMsgTotal                          Counter32,
        apDdAgentRejectedMsgPerMax                         Counter32,
        apDdAgentDroppedMsgRecent                          Gauge32,
        apDdAgentDroppedMsgTotal                           Counter32,
        apDdAgentDroppedMsgPerMax                          Counter32,
        apDdAgentInboundConstraintsRecent                  Gauge32,
        apDdAgentInboundConstraintsTotal                   Counter32,
        apDdAgentInboundConstraintsPerMax                  Counter32,
        apDdAgentOutboundConstraintsRecent                 Gauge32,
        apDdAgentOutboundConstraintsTotal                  Counter32,
        apDdAgentOutboundConstraintsPerMax                 Counter32
}

apDdAgentNoRouteFoundRecent	OBJECT-TYPE
	SYNTAX		Gauge32
	MAX-ACCESS 	read-only
	STATUS		current
	DESCRIPTION
	    "Number of 'no route found' error in recent period."
	::= {apDdAgentErrorStatusEntry 1}

apDdAgentNoRouteFoundTotal	OBJECT-TYPE
	SYNTAX		Counter32
	MAX-ACCESS 	read-only
	STATUS		current
	DESCRIPTION
	    "Total number of 'no route found' error in life time."
	::= {apDdAgentErrorStatusEntry 2}

apDdAgentNoRouteFoundPerMax	OBJECT-TYPE
	SYNTAX		Counter32
	MAX-ACCESS 	read-only
	STATUS		current
	DESCRIPTION
	    "Maximum value of apDdAgentNoRouteFoundRecent across all periods (high water mark)."
	::= {apDdAgentErrorStatusEntry 3}

apDdAgentMalformedMsgRecent	OBJECT-TYPE
	SYNTAX		Gauge32
	MAX-ACCESS 	read-only
	STATUS		current
	DESCRIPTION
	    "Number of 'mal-formed message' error in recent period."
	::= {apDdAgentErrorStatusEntry 4}

apDdAgentMalformedMsgTotal	OBJECT-TYPE
	SYNTAX		Counter32
	MAX-ACCESS 	read-only
	STATUS		current
	DESCRIPTION
	    "Total number of 'mal-formed message' error in life time."
	::= {apDdAgentErrorStatusEntry 5}

apDdAgentMalformedMsgPerMax	OBJECT-TYPE
	SYNTAX		Counter32
	MAX-ACCESS 	read-only
	STATUS		current
	DESCRIPTION
	    "Maximum value of apDdAgentMalformedMsgRecent across all periods (high water mark)."
	::= {apDdAgentErrorStatusEntry 6}



apDdAgentRejectedMsgRecent	OBJECT-TYPE
	SYNTAX		Gauge32
	MAX-ACCESS 	read-only
	STATUS		current
	DESCRIPTION
	    "Number of 'rejected msg'' error in recent period."
	::= {apDdAgentErrorStatusEntry 7}

apDdAgentRejectedMsgTotal	OBJECT-TYPE
	SYNTAX		Counter32
	MAX-ACCESS 	read-only
	STATUS		current
	DESCRIPTION
	    "Total number of 'rejected msg' error in life time."
	::= {apDdAgentErrorStatusEntry 8}

apDdAgentRejectedMsgPerMax	OBJECT-TYPE
	SYNTAX		Counter32
	MAX-ACCESS 	read-only
	STATUS		current
	DESCRIPTION
	    "Maximum value of apDdAgentRejectedMsgRecent across all periods (high water mark)."
	::= {apDdAgentErrorStatusEntry 9}

apDdAgentDroppedMsgRecent	OBJECT-TYPE
	SYNTAX		Gauge32
	MAX-ACCESS 	read-only
	STATUS		current
	DESCRIPTION
	    "Number of 'dropped msg'' error in recent period."
	::= {apDdAgentErrorStatusEntry 10}

apDdAgentDroppedMsgTotal	OBJECT-TYPE
	SYNTAX		Counter32
	MAX-ACCESS 	read-only
	STATUS		current
	DESCRIPTION
	    "Total number of 'dropped msg' error in life time."
	::= {apDdAgentErrorStatusEntry 11}

apDdAgentDroppedMsgPerMax	OBJECT-TYPE
	SYNTAX		Counter32
	MAX-ACCESS 	read-only
	STATUS		current
	DESCRIPTION
	    "Maximum value of apDdAgentDroppedMsgRecent across all periods (high water mark)."
	::= {apDdAgentErrorStatusEntry 12}

apDdAgentInboundConstraintsRecent	OBJECT-TYPE
	SYNTAX		Gauge32
	MAX-ACCESS 	read-only
	STATUS		current
	DESCRIPTION
	    "Number of 'inbound constraints'' error in recent period."
	::= {apDdAgentErrorStatusEntry 13}

apDdAgentInboundConstraintsTotal	OBJECT-TYPE
	SYNTAX		Counter32
	MAX-ACCESS 	read-only
	STATUS		current
	DESCRIPTION
	    "Total number of 'inbound constraints' error in life time."
	::= {apDdAgentErrorStatusEntry 14}

apDdAgentInboundConstraintsPerMax	OBJECT-TYPE
	SYNTAX		Counter32
	MAX-ACCESS 	read-only
	STATUS		current
	DESCRIPTION
	    "Maximum value of apDdAgentInboundConstraintsRecent across all periods (high water mark)."
	::= {apDdAgentErrorStatusEntry 15}

apDdAgentOutboundConstraintsRecent	OBJECT-TYPE
	SYNTAX		Gauge32
	MAX-ACCESS 	read-only
	STATUS		current
	DESCRIPTION
	    "Number of 'outbound constraints'' error in recent period."
	::= {apDdAgentErrorStatusEntry 16}

apDdAgentOutboundConstraintsTotal	OBJECT-TYPE
	SYNTAX		Counter32
	MAX-ACCESS 	read-only
	STATUS		current
	DESCRIPTION
	    "Total number of 'outbound constraints' error in life time."
	::= {apDdAgentErrorStatusEntry 17}

apDdAgentOutboundConstraintsPerMax	OBJECT-TYPE
	SYNTAX		Counter32
	MAX-ACCESS 	read-only
	STATUS		current
	DESCRIPTION
	    "Maximum value of apDdAgentOutboundConstraintsRecent across all periods (high water mark)."
	::= {apDdAgentErrorStatusEntry 18}



apDdAgentMsgTypeStatsTable       	OBJECT-TYPE
        SYNTAX          SEQUENCE OF ApDdAgentMsgTypeStatsEntry
        MAX-ACCESS      not-accessible
        STATUS          current
        DESCRIPTION
	    "table for holding message type stats."
        ::= { apDDMIBTabularObjects 9 }

apDdAgentMsgTypeStatsEntry         OBJECT-TYPE
        SYNTAX          ApDdAgentMsgTypeStatsEntry
        MAX-ACCESS      not-accessible
        STATUS          current
        DESCRIPTION
	    "A table entry designed for message type statistics."
        INDEX { apDdAgentIndex, apDdMsgTypeIndex }
        ::= { apDdAgentMsgTypeStatsTable 1 }

ApDdAgentMsgTypeStatsEntry ::= SEQUENCE {
        apDdAgentMsgTypeServerReqRecent                    Gauge32,
        apDdAgentMsgTypeServerReqTotal                     Counter32,
        apDdAgentMsgTypeServerReqPerMax                    Counter32,
        apDdAgentMsgTypeClientReqRecent                    Gauge32,
        apDdAgentMsgTypeClientReqTotal                     Counter32,
        apDdAgentMsgTypeClientReqPerMax                    Counter32,
        apDdAgentMsgTypeServerRetransRecent                Gauge32,
        apDdAgentMsgTypeServerRetransTotal                 Counter32,
        apDdAgentMsgTypeServerRetransPerMax                Counter32,
        apDdAgentMsgTypeClientRetransRecent                Gauge32,
        apDdAgentMsgTypeClientRetransTotal                 Counter32,
        apDdAgentMsgTypeClientRetransPerMax                Counter32,
        apDdAgentMsgTypeServerRespRetransRecent            Gauge32,
        apDdAgentMsgTypeServerRespRetransTotal             Counter32,
        apDdAgentMsgTypeServerRespRetransPerMax            Counter32,
        apDdAgentMsgTypeClientRespRetransRecent            Gauge32,
        apDdAgentMsgTypeClientRespRetransTotal             Counter32,
        apDdAgentMsgTypeClientRespRetransPerMax            Counter32,
        apDdAgentMsgTypeClientTimeoutRecent                Gauge32,
        apDdAgentMsgTypeClientTimeoutTotal                 Counter32,
        apDdAgentMsgTypeClientTimeoutPerMax                Counter32,
        apDdAgentMsgTypeClientThrottledRecent              Gauge32,
        apDdAgentMsgTypeClientThrottledTotal               Counter32,
        apDdAgentMsgTypeClientThrottledPerMax              Counter32,
        apDdAgentMsgTypeAverageLatency                     Gauge32,
        apDdAgentMsgTypeMaximumLatency                     Gauge32,
        apDdAgentMsgTypeLatencyWindow                      Integer32
}

apDdAgentMsgTypeServerReqRecent	OBJECT-TYPE
	SYNTAX			Gauge32
	MAX-ACCESS 		read-only
	STATUS			current
	DESCRIPTION
	    "Number of server requests in recent period."
	::= {apDdAgentMsgTypeStatsEntry 3}

apDdAgentMsgTypeServerReqTotal	OBJECT-TYPE
	SYNTAX			Counter32
	MAX-ACCESS 		read-only
	STATUS			current
	DESCRIPTION
	    "Total number of server requests in life time."
	::= {apDdAgentMsgTypeStatsEntry 4}

apDdAgentMsgTypeServerReqPerMax	OBJECT-TYPE
	SYNTAX			Counter32
	MAX-ACCESS 		read-only
	STATUS			current
	DESCRIPTION
	    "Maximum value of apDdAgentMsgTypeServerReqRecent across all periods (high water mark)"
	::= {apDdAgentMsgTypeStatsEntry 5}

apDdAgentMsgTypeClientReqRecent	OBJECT-TYPE
	SYNTAX			Gauge32
	MAX-ACCESS 		read-only
	STATUS			current
	DESCRIPTION
	    "Number of client requests in recent period."
	::= {apDdAgentMsgTypeStatsEntry 6}

apDdAgentMsgTypeClientReqTotal	OBJECT-TYPE
	SYNTAX			Counter32
	MAX-ACCESS 		read-only
	STATUS			current
	DESCRIPTION
	    "Total number of client requests in life time."
	::= {apDdAgentMsgTypeStatsEntry 7}

apDdAgentMsgTypeClientReqPerMax	OBJECT-TYPE
	SYNTAX			Counter32
	MAX-ACCESS 		read-only
	STATUS			current
	DESCRIPTION
	    "Maximum value of apDdAgentMsgTypeClientReqRecent across all periods (high water mark)."
	::= {apDdAgentMsgTypeStatsEntry 8}

apDdAgentMsgTypeServerRetransRecent	OBJECT-TYPE
	SYNTAX			Gauge32
	MAX-ACCESS 		read-only
	STATUS			current
	DESCRIPTION
	    "Number of server retransmissions in recent period."
	::= {apDdAgentMsgTypeStatsEntry 9}

apDdAgentMsgTypeServerRetransTotal	OBJECT-TYPE
	SYNTAX			Counter32
	MAX-ACCESS 		read-only
	STATUS			current
	DESCRIPTION
	    "Total number of server retransmissions in life time."
	::= {apDdAgentMsgTypeStatsEntry 10}

apDdAgentMsgTypeServerRetransPerMax	OBJECT-TYPE
	SYNTAX			Counter32
	MAX-ACCESS 		read-only
	STATUS			current
	DESCRIPTION
	    "Maximum value of apDdAgentMsgTypeServerRetransRecent across all periods (high water mark)"
	::= {apDdAgentMsgTypeStatsEntry 11}

apDdAgentMsgTypeClientRetransRecent	OBJECT-TYPE
	SYNTAX			Gauge32
	MAX-ACCESS 		read-only
	STATUS			current
	DESCRIPTION
	    "Number of client retransmissions in recent period."
	::= {apDdAgentMsgTypeStatsEntry 12}

apDdAgentMsgTypeClientRetransTotal	OBJECT-TYPE
	SYNTAX			Counter32
	MAX-ACCESS 		read-only
	STATUS			current
	DESCRIPTION
	    "Total number of client retransmissions in life time."
	::= {apDdAgentMsgTypeStatsEntry 13}

apDdAgentMsgTypeClientRetransPerMax	OBJECT-TYPE
	SYNTAX			Counter32
	MAX-ACCESS 		read-only
	STATUS			current
	DESCRIPTION
	    "Maximum value of apDdAgentMsgTypeClientRetransRecent across all periods (high water mark)."
	::= {apDdAgentMsgTypeStatsEntry 14}

apDdAgentMsgTypeServerRespRetransRecent	OBJECT-TYPE
	SYNTAX			Gauge32
	MAX-ACCESS 		read-only
	STATUS			current
	DESCRIPTION
	    "Number of server response retransactions in recent period."
	::= {apDdAgentMsgTypeStatsEntry 15}

apDdAgentMsgTypeServerRespRetransTotal	OBJECT-TYPE
	SYNTAX			Counter32
	MAX-ACCESS 		read-only
	STATUS			current
	DESCRIPTION
	    "Total number of server response retransactions in life time."
	::= {apDdAgentMsgTypeStatsEntry 16}

apDdAgentMsgTypeServerRespRetransPerMax	OBJECT-TYPE
	SYNTAX			Counter32
	MAX-ACCESS 		read-only
	STATUS			current
	DESCRIPTION
	    "Maximum value of apDdAgentMsgTypeServerRespRetransRecent across all periods (high water mark)."
	::= {apDdAgentMsgTypeStatsEntry 17}

apDdAgentMsgTypeClientRespRetransRecent	OBJECT-TYPE
	SYNTAX			Gauge32
	MAX-ACCESS 		read-only
	STATUS			current
	DESCRIPTION
	    "Number of client response retransactions in recent period."
	::= {apDdAgentMsgTypeStatsEntry 21}

apDdAgentMsgTypeClientRespRetransTotal	OBJECT-TYPE
	SYNTAX			Counter32
	MAX-ACCESS 		read-only
	STATUS			current
	DESCRIPTION
	    "Total number of client response retransactions in life time."
	::= {apDdAgentMsgTypeStatsEntry 22}

apDdAgentMsgTypeClientRespRetransPerMax	OBJECT-TYPE
	SYNTAX			Counter32
	MAX-ACCESS 		read-only
	STATUS			current
	DESCRIPTION
	    "Maximum value of apDdAgentMsgTypeClientRespRetransRecent across all periods (high water mark)."
	::= {apDdAgentMsgTypeStatsEntry 23}

apDdAgentMsgTypeClientTimeoutRecent	OBJECT-TYPE
	SYNTAX			Gauge32
	MAX-ACCESS 		read-only
	STATUS			current
	DESCRIPTION
	    "Number of client transaction timeout in recent period."
	::= {apDdAgentMsgTypeStatsEntry 27}

apDdAgentMsgTypeClientTimeoutTotal	OBJECT-TYPE
	SYNTAX			Counter32
	MAX-ACCESS 		read-only
	STATUS			current
	DESCRIPTION
	    "Total number of client transaction timeout in life time."
	::= {apDdAgentMsgTypeStatsEntry 28}

apDdAgentMsgTypeClientTimeoutPerMax	OBJECT-TYPE
	SYNTAX			Counter32
	MAX-ACCESS 		read-only
	STATUS			current
	DESCRIPTION
	    "Maximum value of apDdAgentMsgTypeClientTimeoutRecent across all periods (high water mark)."
	::= {apDdAgentMsgTypeStatsEntry 29}

apDdAgentMsgTypeClientThrottledRecent	OBJECT-TYPE
	SYNTAX			Gauge32
	MAX-ACCESS 		read-only
	STATUS			current
	DESCRIPTION
	    "Number of locally throttled client count in recent period."
	::= {apDdAgentMsgTypeStatsEntry 33}

apDdAgentMsgTypeClientThrottledTotal	OBJECT-TYPE
	SYNTAX			Counter32
	MAX-ACCESS 		read-only
	STATUS			current
	DESCRIPTION
	    "Total number of locally throttled client count in life time."
	::= {apDdAgentMsgTypeStatsEntry 34}

apDdAgentMsgTypeClientThrottledPerMax	OBJECT-TYPE
	SYNTAX			Counter32
	MAX-ACCESS 		read-only
	STATUS			current
	DESCRIPTION
	    "Maximum value of apDdAgentMsgTypeClientThrottledRecent across all periods (high water mark)."
	::= {apDdAgentMsgTypeStatsEntry 35}

apDdAgentMsgTypeAverageLatency	OBJECT-TYPE
	SYNTAX			Gauge32
	MAX-ACCESS 		read-only
	STATUS			current
	DESCRIPTION
	    "Average Latency."
	::= {apDdAgentMsgTypeStatsEntry 36}

apDdAgentMsgTypeMaximumLatency	OBJECT-TYPE
	SYNTAX			Gauge32
	MAX-ACCESS 		read-only
	STATUS			current
	DESCRIPTION
	    "Maximum Latency."
	::= {apDdAgentMsgTypeStatsEntry 37}

apDdAgentMsgTypeLatencyWindow	OBJECT-TYPE
	SYNTAX			Integer32
	UNITS			"second"
	MAX-ACCESS 		read-only
	STATUS			current
	DESCRIPTION
	    "Latency window length."
	::= {apDdAgentMsgTypeStatsEntry 38}



apDdAgentMsgStatsReturnCodeTable       	OBJECT-TYPE
        SYNTAX          SEQUENCE OF ApDdAgentMsgStatsReturnCodeEntry
        MAX-ACCESS      not-accessible
        STATUS          current
        DESCRIPTION
	    "DD return message code stats table."
        ::= { apDDMIBTabularObjects 10 }

apDdAgentMsgStatsReturnCodeEntry         OBJECT-TYPE
        SYNTAX          ApDdAgentMsgStatsReturnCodeEntry
        MAX-ACCESS      not-accessible
        STATUS          current
        DESCRIPTION
	    "A table entry designed to hold return code stats."
        INDEX 
	{ apDdAgentIndex, apDdMsgTypeIndex, apDdMsgReturnCodeIndex }
        ::= { apDdAgentMsgStatsReturnCodeTable 1 }

ApDdAgentMsgStatsReturnCodeEntry ::= SEQUENCE {
        apDdAgentMsgReturnCodeServerRecent                 Gauge32,
        apDdAgentMsgReturnCodeServerTotal                  Counter32,
        apDdAgentMsgReturnCodeServerPerMax                 Counter32,
        apDdAgentMsgReturnCodeClientRecent                 Gauge32,
        apDdAgentMsgReturnCodeClientTotal                  Counter32,
        apDdAgentMsgReturnCodeClientPerMax                 Counter32
}

apDdAgentMsgReturnCodeServerRecent	OBJECT-TYPE
	SYNTAX			Gauge32
	MAX-ACCESS 		read-only
	STATUS			current
	DESCRIPTION
	    "Number of server requests in recent period."
	::= {apDdAgentMsgStatsReturnCodeEntry 3}

apDdAgentMsgReturnCodeServerTotal	OBJECT-TYPE
	SYNTAX			Counter32
	MAX-ACCESS 		read-only
	STATUS			current
	DESCRIPTION
	    "Total number of server requests in life time."
	::= {apDdAgentMsgStatsReturnCodeEntry 4}

apDdAgentMsgReturnCodeServerPerMax	OBJECT-TYPE
	SYNTAX			Counter32
	MAX-ACCESS 		read-only
	STATUS			current
	DESCRIPTION
	    "Maximum value of apDdAgentMsgReturnCodeServerRecent across all periods (high water mark)."
	::= {apDdAgentMsgStatsReturnCodeEntry 5}

apDdAgentMsgReturnCodeClientRecent	OBJECT-TYPE
	SYNTAX			Gauge32
	MAX-ACCESS 		read-only
	STATUS			current
	DESCRIPTION
	    "Number of server requests in recent period."
	::= {apDdAgentMsgStatsReturnCodeEntry 6}

apDdAgentMsgReturnCodeClientTotal	OBJECT-TYPE
	SYNTAX			Counter32
	MAX-ACCESS 		read-only
	STATUS			current
	DESCRIPTION
	    "Total number of server requests in life time."
	::= {apDdAgentMsgStatsReturnCodeEntry 7}

apDdAgentMsgReturnCodeClientPerMax	OBJECT-TYPE
	SYNTAX			Counter32
	MAX-ACCESS 		read-only
	STATUS			current
	DESCRIPTION
	    "Maximum value of apDdAgentMsgReturnCodeClientRecent across all periods (high water mark)."
	::= {apDdAgentMsgStatsReturnCodeEntry 8}
	
apDdAgentDnsStatsTable       	OBJECT-TYPE
        SYNTAX          SEQUENCE OF ApDdAgentDnsStatsEntry
        MAX-ACCESS      not-accessible
        STATUS          current
        DESCRIPTION
	    "per DD Agent dns stats."
        ::= { apDDMIBTabularObjects 12 }

apDdAgentDnsStatsEntry         OBJECT-TYPE
        SYNTAX          ApDdAgentDnsStatsEntry
        MAX-ACCESS      not-accessible
        STATUS          current
        DESCRIPTION
	    "A table entry designed to hold dns stats data"
        INDEX { apDdAgentIndex }
        ::= { apDdAgentDnsStatsTable 1 }

ApDdAgentDnsStatsEntry ::= SEQUENCE {
        apDdAgentDnsQueriesRecent                        Gauge32,
        apDdAgentDnsQueriesTotal                         Counter32,
        apDdAgentDnsQueriesPerMax                        Counter32,
        apDdAgentDnsCacheHitsRecent                      Gauge32,
        apDdAgentDnsCacheHitsTotal                       Counter32,
        apDdAgentDnsCacheHitsPerMax                      Counter32,
        apDdAgentDnsCacheMissesRecent                    Gauge32,
        apDdAgentDnsCacheMissesTotal                     Counter32,
        apDdAgentDnsCacheMissesPerMax                    Counter32,
        apDdAgentDnsClientErrorsRecent                   Gauge32,
        apDdAgentDnsClientErrorsTotal                    Counter32,
        apDdAgentDnsClientErrorsPerMax                   Counter32,
        apDdAgentDnsServerErrorsRecent                   Gauge32,
        apDdAgentDnsServerErrorsTotal                    Counter32,
        apDdAgentDnsServerErrorsPerMax                   Counter32,
        apDdAgentDnsResponsesRecent                      Gauge32,
        apDdAgentDnsResponsesTotal                       Counter32,
        apDdAgentDnsResponsesPerMax                      Counter32
}
apDdAgentDnsQueriesRecent	OBJECT-TYPE
	SYNTAX		Gauge32
	MAX-ACCESS 	read-only
	STATUS		current
	DESCRIPTION
	    "Number of dns queries in recent period."
	::= {apDdAgentDnsStatsEntry 1}

apDdAgentDnsQueriesTotal	    OBJECT-TYPE
	SYNTAX		Counter32
	MAX-ACCESS 	read-only
	STATUS		current
	DESCRIPTION
	    "Number of dns queries in total period."
	::= {apDdAgentDnsStatsEntry 2}


apDdAgentDnsQueriesPerMax	OBJECT-TYPE
	SYNTAX		Counter32
	MAX-ACCESS 	read-only
	STATUS		current
	DESCRIPTION
	    "Maximum value of apDdAgentDnsQueriesRecent across all periods (high water mark)."
	::= {apDdAgentDnsStatsEntry 3}

apDdAgentDnsCacheHitsRecent	OBJECT-TYPE
	SYNTAX		Gauge32
	MAX-ACCESS 	read-only
	STATUS		current
	DESCRIPTION
	    "Number of dns cache hits in recent period."
	::= {apDdAgentDnsStatsEntry 4}

apDdAgentDnsCacheHitsTotal	    OBJECT-TYPE
	SYNTAX		Counter32
	MAX-ACCESS 	read-only
	STATUS		current
	DESCRIPTION
	    "Number of dns cache hits in total period."
	::= {apDdAgentDnsStatsEntry 5}


apDdAgentDnsCacheHitsPerMax	OBJECT-TYPE
	SYNTAX		Counter32
	MAX-ACCESS 	read-only
	STATUS		current
	DESCRIPTION
	    "Maximum value of apDdAgentDnsCacheHitsRecent across all periods (high water mark)."
	::= {apDdAgentDnsStatsEntry 6}

apDdAgentDnsCacheMissesRecent	OBJECT-TYPE
	SYNTAX		Gauge32
	MAX-ACCESS 	read-only
	STATUS		current
	DESCRIPTION
	    "Number of dns cache misses in recent period."
	::= {apDdAgentDnsStatsEntry 7}

apDdAgentDnsCacheMissesTotal	    OBJECT-TYPE
	SYNTAX		Counter32
	MAX-ACCESS 	read-only
	STATUS		current
	DESCRIPTION
	    "Number of dns cache misses in total period."
	::= {apDdAgentDnsStatsEntry 8}


apDdAgentDnsCacheMissesPerMax	OBJECT-TYPE
	SYNTAX		Counter32
	MAX-ACCESS 	read-only
	STATUS		current
	DESCRIPTION
	    "Maximum value of apDdAgentDnsCacheMissesRecent across all periods (high water mark)."
	::= {apDdAgentDnsStatsEntry 9}	
	
apDdAgentDnsClientErrorsRecent	OBJECT-TYPE
	SYNTAX		Gauge32
	MAX-ACCESS 	read-only
	STATUS		current
	DESCRIPTION
	    "Number of dns client errors in recent period."
	::= {apDdAgentDnsStatsEntry 10}

apDdAgentDnsClientErrorsTotal	    OBJECT-TYPE
	SYNTAX		Counter32
	MAX-ACCESS 	read-only
	STATUS		current
	DESCRIPTION
	    "Number of dns client errors in total period."
	::= {apDdAgentDnsStatsEntry 11}


apDdAgentDnsClientErrorsPerMax	OBJECT-TYPE
	SYNTAX		Counter32
	MAX-ACCESS 	read-only
	STATUS		current
	DESCRIPTION
	    "Maximum value of apDdAgentDnsClientErrorsRecent across all periods (high water mark)."
	::= {apDdAgentDnsStatsEntry 12}
		
apDdAgentDnsServerErrorsRecent	OBJECT-TYPE
	SYNTAX		Gauge32
	MAX-ACCESS 	read-only
	STATUS		current
	DESCRIPTION
	    "Number of dns server errors in recent period."
	::= {apDdAgentDnsStatsEntry 13}

apDdAgentDnsServerErrorsTotal	    OBJECT-TYPE
	SYNTAX		Counter32
	MAX-ACCESS 	read-only
	STATUS		current
	DESCRIPTION
	    "Number of dns server errors in total period."
	::= {apDdAgentDnsStatsEntry 14}


apDdAgentDnsServerErrorsPerMax	OBJECT-TYPE
	SYNTAX		Counter32
	MAX-ACCESS 	read-only
	STATUS		current
	DESCRIPTION
	    "Maximum value of apDdAgentDnsServerErrorsRecent across all periods (high water mark)."
	::= {apDdAgentDnsStatsEntry 15}	
		
apDdAgentDnsResponsesRecent	OBJECT-TYPE
	SYNTAX		Gauge32
	MAX-ACCESS 	read-only
	STATUS		current
	DESCRIPTION
	    "Number of dns responses in recent period."
	::= {apDdAgentDnsStatsEntry 16}

apDdAgentDnsResponsesTotal	    OBJECT-TYPE
	SYNTAX		Counter32
	MAX-ACCESS 	read-only
	STATUS		current
	DESCRIPTION
	    "Number of dns responses in total period."
	::= {apDdAgentDnsStatsEntry 17}


apDdAgentDnsResponsesPerMax	OBJECT-TYPE
	SYNTAX		Counter32
	MAX-ACCESS 	read-only
	STATUS		current
	DESCRIPTION
	    "Maximum value of apDdAgentDnsResponsesRecent across all periods (high water mark)."
	::= {apDdAgentDnsStatsEntry 18}	

	
	
	
	
	
	
	

-- End of Agent Tabular Object

-- Notifications

apDdDiameterAgentHostName	OBJECT-TYPE
	SYNTAX     	     	DisplayString (SIZE (1..255))
	MAX-ACCESS		accessible-for-notify
	STATUS	   		current
	DESCRIPTION
	    "The hostname of the Diameter Agent where it is hosted."
	::= { apDDNotifObjects 1 }

apDdDiameterIPPort		OBJECT-TYPE
	SYNTAX     	     	DisplayString (SIZE (1..255))
	MAX-ACCESS		accessible-for-notify
	STATUS	   		current
	DESCRIPTION
	    "The IP port of the Diameter Agent where it is hosted."
	::= { apDDNotifObjects 2 }

apDdDiameterAgentOriginHostName	OBJECT-TYPE
	SYNTAX     	     	DisplayString (SIZE (1..255))
	MAX-ACCESS		accessible-for-notify
	STATUS	   		current
	DESCRIPTION
	    "The origin hostname of the Diameter Agent where it is hosted."
	::= { apDDNotifObjects 3 }

apDdDiameterAgentOriginRealmName	OBJECT-TYPE
	SYNTAX     	     	DisplayString (SIZE (1..255))
	MAX-ACCESS		accessible-for-notify
	STATUS	   		current
	DESCRIPTION
	    "The origin realm name of the Diameter Agent where it is hosted."
	::= { apDDNotifObjects 4 }

apDdTransportType		OBJECT-TYPE
	SYNTAX			ApTransportType
	MAX-ACCESS		accessible-for-notify
	STATUS	   		current
	DESCRIPTION
	    "The transport type of the DD interface."
	::= { apDDNotifObjects 5 }

apDdInterfaceStatusReason	OBJECT-TYPE
	SYNTAX     	     	INTEGER {    
				        disconnectByRequest(0),
					diameterAgentUnreachable(1),
					transportFailure(2)
				}
	MAX-ACCESS		accessible-for-notify
	STATUS	   		current
	DESCRIPTION
	"The reason for the status change on a DD interface"
	::= { apDDNotifObjects 6 }

apDdDiameterRemoteIPPort	OBJECT-TYPE
	SYNTAX			DisplayString (SIZE (1..255))
	MAX-ACCESS		accessible-for-notify
	STATUS			current
	DESCRIPTION
	    "The IP port of the remote host."
	::= { apDDNotifObjects 7 }

apDdSCTPAssociationID		OBJECT-TYPE
	SYNTAX			Integer32
	MAX-ACCESS		accessible-for-notify
	STATUS			current
	DESCRIPTION
	    "The ID of the SCTP association."
	::= { apDDNotifObjects 8 }

apDdSCTPIsPrimaryPath		OBJECT-TYPE
	SYNTAX			TruthValue
	MAX-ACCESS		accessible-for-notify
	STATUS			current
	DESCRIPTION
	    "Indicates if this SCTP path becomes the new primary path."
	::= { apDDNotifObjects 9 }


apDdConnectionFailureTrap NOTIFICATION-TYPE
        OBJECTS {
		apDdInterfaceRealmName,
		apDdDiameterAgentHostName,
		apDdDiameterIPPort,
		apDdDiameterAgentOriginHostName,
		apDdDiameterAgentOriginRealmName,
		apDdTransportType,
		apDdInterfaceStatusReason
                }
        STATUS  current
        DESCRIPTION
	    "A notification when a diameter connection is disconnected 
	    via a disconnect request."
        ::= { apDDNotifications 1 }

apDdConnectionFailureClearTrap NOTIFICATION-TYPE
        OBJECTS {
		apDdInterfaceRealmName,
		apDdDiameterAgentHostName,
		apDdDiameterIPPort,
		apDdDiameterAgentOriginHostName,
		apDdDiameterAgentOriginRealmName,
		apDdTransportType,
		apDdInterfaceStatusReason
                }
        STATUS  current
        DESCRIPTION
	    "A notification when a transport failure has been recovered."
        ::= { apDDNotifications 2 }

apDdSCTPPathFailureTrap NOTIFICATION-TYPE
        OBJECTS {
		apDdInterfaceRealmName,
		apDdDiameterAgentHostName,
		apDdDiameterIPPort,
		apDdDiameterAgentOriginHostName,
		apDdDiameterAgentOriginRealmName,
		apDdDiameterRemoteIPPort,
		apDdSCTPAssociationID,
		apDdSCTPIsPrimaryPath
                }
        STATUS  current
        DESCRIPTION
	    "A notification when a SCTP path fails."
        ::= { apDDNotifications 3 }

apDdSCTPPathFailureClearTrap NOTIFICATION-TYPE
        OBJECTS {
		apDdInterfaceRealmName,
		apDdDiameterAgentHostName,
		apDdDiameterIPPort,
		apDdDiameterAgentOriginHostName,
		apDdDiameterAgentOriginRealmName,
		apDdDiameterRemoteIPPort,
		apDdSCTPAssociationID,
		apDdSCTPIsPrimaryPath
                }
        STATUS  current
        DESCRIPTION
        "A notification when a SCTP path failure has been recovered."
        ::= { apDDNotifications 4 }

-- compliance statements

-- units of conformance


----------------------------------------------------
--
-- apDdObjectGroups
--
----------------------------------------------------

apDdGeneralGroup OBJECT-GROUP
      OBJECTS {
		apDdInterfaceNumber,
		apDdCurrentTransRate,
		apDdHighTransRate,
		apDdLowTransRate
	         }
      STATUS		current
      DESCRIPTION
	  "A collection of objects generic to DD system."
      ::= {  apDDObjectGroups 1 }

apDdInterfaceStatsGroup OBJECT-GROUP
    OBJECTS {
        apDdInterfaceRealmName,
        apDdClientTransCPActive,
        apDdClientTransCPHigh,
        apDdClientTransCPTotal,
        apDdClientTransLTTotal,
        apDdClientTransLTPerMax,
        apDdClientTransLTHigh,
        apDdServerTransCPActive,
        apDdServerTransCPHigh,
        apDdServerTransCPTotal,
        apDdServerTransLTTotal,
        apDdServerTransLTPerMax,
        apDdServerTransLTHigh,
        apDdGenSocketsCPActive,
        apDdGenSocketsCPHigh,
        apDdGenSocketsCPTotal,
        apDdGenSocketsLTTotal,
        apDdGenSocketsLTPerMax,
        apDdGenSocketsLTHigh,
        apDdGenConnectsCPActive,
        apDdGenConnectsCPHigh,
        apDdGenConnectsCPTotal,
        apDdGenConnectsLTTotal,
        apDdGenConnectsLTPerMax,
        apDdGenConnectsLTHigh,
        apDdInterfaceStatus
	     }
      STATUS		current
      DESCRIPTION
	  "A collection of statistics for DD interfaces or system."
      ::= {  apDDObjectGroups 2 }

apDdErrorStatusGroup OBJECT-GROUP
    OBJECTS {
        apDdNoRouteFoundRecent,
        apDdNoRouteFoundTotal,
        apDdNoRouteFoundPerMax,
        apDdMalformedMsgRecent,
        apDdMalformedMsgTotal,
        apDdMalformedMsgPerMax
	     }
      STATUS		current
      DESCRIPTION
	  "A collection of statistics for DD errors."
      ::= {  apDDObjectGroups 3 }

apDdMsgTypeStatsGroup OBJECT-GROUP
    OBJECTS {
        apDdMsgTypeMsgName,
        apDdMsgTypeServerReqRecent,
        apDdMsgTypeServerReqTotal,
        apDdMsgTypeServerReqPerMax,
        apDdMsgTypeClientReqRecent,
        apDdMsgTypeClientReqTotal,
        apDdMsgTypeClientReqPerMax,
        apDdMsgTypeServerRetransRecent,
        apDdMsgTypeServerRetransTotal,
        apDdMsgTypeServerRetransPerMax,
        apDdMsgTypeClientRetransRecent,
        apDdMsgTypeClientRetransTotal,
        apDdMsgTypeClientRetransPerMax,
        apDdMsgTypeServerRespRetransRecent,
        apDdMsgTypeServerRespRetransTotal,
        apDdMsgTypeServerRespRetransPerMax,
        apDdMsgTypeClientRespRetransRecent,
        apDdMsgTypeClientRespRetransTotal,
        apDdMsgTypeClientRespRetransPerMax,
        apDdMsgTypeClientTimeoutRecent,
        apDdMsgTypeClientTimeoutTotal,
        apDdMsgTypeClientTimeoutPerMax,
        apDdMsgTypeClientThrottledRecent,
        apDdMsgTypeClientThrottledTotal,
        apDdMsgTypeClientThrottledPerMax,
        apDdMsgTypeAverageLatency,
        apDdMsgTypeMaximumLatency,
        apDdMsgTypeLatencyWindow
	     }
      STATUS		current
      DESCRIPTION
	  "A collection of statistics for DD message types."
      ::= {  apDDObjectGroups 4 }

apDdMsgStatsReturnCodeGroup OBJECT-GROUP
    OBJECTS {
        apDdMsgReturnCodeName,
        apDdMsgReturnCodeServerRecent,
        apDdMsgReturnCodeServerTotal,
        apDdMsgReturnCodeServerPerMax,
        apDdMsgReturnCodeClientRecent,
        apDdMsgReturnCodeClientTotal,
        apDdMsgReturnCodeClientPerMax
	     }
      STATUS		current
      DESCRIPTION
	  "A collection of statistics for DD message type return codes."
      ::= {  apDDObjectGroups 5 }

apDdIntfErrorStatusGroup OBJECT-GROUP
    OBJECTS {
        apDdRejectedMsgRecent,            
        apDdRejectedMsgTotal,             
        apDdRejectedMsgPerMax,            
        apDdDroppedMsgRecent,             
        apDdDroppedMsgTotal,              
        apDdDroppedMsgPerMax,             
        apDdInboundConstraintsRecent,
        apDdInboundConstraintsTotal,      
        apDdInboundConstraintsPerMax,     
        apDdOutboundConstraintsRecent,    
        apDdOutboundConstraintsTotal,     
        apDdOutboundConstraintsPerMax    
	     }
      STATUS		current
      DESCRIPTION
	  "A collection of statistics for DD errors."
      ::= {  apDDObjectGroups 6 }

-- End of General & Interface Stats Group

-- Start Agent Stats Group


apDdAgentGeneralGroup OBJECT-GROUP
      OBJECTS {
		apDdAgentNumber
	         }
      STATUS		current
      DESCRIPTION
	  "A collection of Agent objects generic to DD system."
      ::= {  apDDObjectGroups 7 }

apDdAgentStatsGroup OBJECT-GROUP
    OBJECTS {
        apDdAgentRealmName,
        apDdAgentClientTransCPActive,
        apDdAgentClientTransCPHigh,
        apDdAgentClientTransCPTotal,
        apDdAgentClientTransLTTotal,
        apDdAgentClientTransLTPerMax,
        apDdAgentClientTransLTHigh,
        apDdAgentServerTransCPActive,
        apDdAgentServerTransCPHigh,
        apDdAgentServerTransCPTotal,
        apDdAgentServerTransLTTotal,
        apDdAgentServerTransLTPerMax,
        apDdAgentServerTransLTHigh,
        apDdAgentGenSocketsCPActive,
        apDdAgentGenSocketsCPHigh,
        apDdAgentGenSocketsCPTotal,
        apDdAgentGenSocketsLTTotal,
        apDdAgentGenSocketsLTPerMax,
        apDdAgentGenSocketsLTHigh,
        apDdAgentGenConnectsCPActive,
        apDdAgentGenConnectsCPHigh,
        apDdAgentGenConnectsCPTotal,
        apDdAgentGenConnectsLTTotal,
        apDdAgentGenConnectsLTPerMax,
        apDdAgentGenConnectsLTHigh,
        apDdAgentStatus
	     }
      STATUS		current
      DESCRIPTION
	  "A collection of statistics for DD agents"
      ::= {  apDDObjectGroups 8 }

apDdAgentErrorStatusGroup OBJECT-GROUP
    OBJECTS {
        apDdAgentNoRouteFoundRecent,
        apDdAgentNoRouteFoundTotal,
        apDdAgentNoRouteFoundPerMax,
        apDdAgentMalformedMsgRecent,
        apDdAgentMalformedMsgTotal,
        apDdAgentMalformedMsgPerMax,
        apDdAgentRejectedMsgRecent,         
        apDdAgentRejectedMsgTotal,          
        apDdAgentRejectedMsgPerMax,         
        apDdAgentDroppedMsgRecent,          
        apDdAgentDroppedMsgTotal,           
        apDdAgentDroppedMsgPerMax,          
        apDdAgentInboundConstraintsRecent,  
        apDdAgentInboundConstraintsTotal,   
        apDdAgentInboundConstraintsPerMax,  
        apDdAgentOutboundConstraintsRecent, 
        apDdAgentOutboundConstraintsTotal,  
        apDdAgentOutboundConstraintsPerMax
	     }
      STATUS		current
      DESCRIPTION
	  "A collection of statistics for DD Agent errors."
      ::= {  apDDObjectGroups 9 }

apDdAgentMsgTypeStatsGroup OBJECT-GROUP
    OBJECTS {
        apDdMsgTypeMsgName,
        apDdAgentMsgTypeServerReqRecent,
        apDdAgentMsgTypeServerReqTotal,
        apDdAgentMsgTypeServerReqPerMax,
        apDdAgentMsgTypeClientReqRecent,
        apDdAgentMsgTypeClientReqTotal,
        apDdAgentMsgTypeClientReqPerMax,
        apDdAgentMsgTypeServerRetransRecent,
        apDdAgentMsgTypeServerRetransTotal,
        apDdAgentMsgTypeServerRetransPerMax,
        apDdAgentMsgTypeClientRetransRecent,
        apDdAgentMsgTypeClientRetransTotal,
        apDdAgentMsgTypeClientRetransPerMax,
        apDdAgentMsgTypeServerRespRetransRecent,
        apDdAgentMsgTypeServerRespRetransTotal,
        apDdAgentMsgTypeServerRespRetransPerMax,
        apDdAgentMsgTypeClientRespRetransRecent,
        apDdAgentMsgTypeClientRespRetransTotal,
        apDdAgentMsgTypeClientRespRetransPerMax,
        apDdAgentMsgTypeClientTimeoutRecent,
        apDdAgentMsgTypeClientTimeoutTotal,
        apDdAgentMsgTypeClientTimeoutPerMax,
        apDdAgentMsgTypeClientThrottledRecent,
        apDdAgentMsgTypeClientThrottledTotal,
        apDdAgentMsgTypeClientThrottledPerMax,
        apDdAgentMsgTypeAverageLatency,
        apDdAgentMsgTypeMaximumLatency,
        apDdAgentMsgTypeLatencyWindow
	     }
      STATUS		current
      DESCRIPTION
	  "A collection of statistics for DD Agent message types."
      ::= {  apDDObjectGroups 10 }

apDdAgentMsgStatsReturnCodeGroup OBJECT-GROUP
    OBJECTS {
        apDdMsgReturnCodeName,
        apDdAgentMsgReturnCodeServerRecent,
        apDdAgentMsgReturnCodeServerTotal,
        apDdAgentMsgReturnCodeServerPerMax,
        apDdAgentMsgReturnCodeClientRecent,
        apDdAgentMsgReturnCodeClientTotal,
        apDdAgentMsgReturnCodeClientPerMax
	     }
      STATUS		current
      DESCRIPTION
	  "A collection of statistics for DD Agent message type return codes."
      ::= {  apDDObjectGroups 11 }
      
 apDdDnsStatsEntryGroup OBJECT-GROUP 
 	OBJECTS {
        apDdDnsQueriesRecent,                       
        apDdDnsQueriesTotal,
        apDdDnsQueriesPerMax,
        apDdDnsCacheHitsRecent,
        apDdDnsCacheHitsTotal,
        apDdDnsCacheHitsPerMax,
        apDdDnsCacheMissesRecent,
        apDdDnsCacheMissesTotal,
        apDdDnsCacheMissesPerMax,
        apDdDnsClientErrorsRecent,
        apDdDnsClientErrorsTotal,
        apDdDnsClientErrorsPerMax,
        apDdDnsServerErrorsRecent,
        apDdDnsServerErrorsTotal,
        apDdDnsServerErrorsPerMax,
        apDdDnsResponsesRecent,
        apDdDnsResponsesTotal,
        apDdDnsResponsesPerMax
}
	  STATUS		current
      DESCRIPTION
	  "A collection of statistics for DD DNS."
      ::= {  apDDObjectGroups 13 }


apDdAgentDnsStatsEntryGroup OBJECT-GROUP 
 	OBJECTS {
        apDdAgentDnsQueriesRecent,                       
        apDdAgentDnsQueriesTotal,
        apDdAgentDnsQueriesPerMax,
        apDdAgentDnsCacheHitsRecent,
        apDdAgentDnsCacheHitsTotal,
        apDdAgentDnsCacheHitsPerMax,
        apDdAgentDnsCacheMissesRecent,
        apDdAgentDnsCacheMissesTotal,
        apDdAgentDnsCacheMissesPerMax,
        apDdAgentDnsClientErrorsRecent,
        apDdAgentDnsClientErrorsTotal,
        apDdAgentDnsClientErrorsPerMax,
        apDdAgentDnsServerErrorsRecent,
        apDdAgentDnsServerErrorsTotal,
        apDdAgentDnsServerErrorsPerMax,
        apDdAgentDnsResponsesRecent,
        apDdAgentDnsResponsesTotal,
        apDdAgentDnsResponsesPerMax
}
	  STATUS		current
      DESCRIPTION
	  "A collection of statistics for DD Agent DNS ."
      ::= {  apDDObjectGroups 14 }
            
      

-- End of Agent Stats Group

-- Start of Session Stats Group

apDdSessionSubscriberGeneralGroup OBJECT-GROUP
      OBJECTS {

--  Session Stats
		apDdSessionPeriodActive,
		apDdSessionPeriodHigh,
                apDdSessionPeriodTotal,
		apDdSessionLifeTotal,
		apDdSessionLifePerMax,
                apDdSessionLifeHigh,

--  Session Initial Stats
                apDdSessInitPeriodActive,
		apDdSessInitPeriodHigh,
                apDdSessInitPeriodTotal,
		apDdSessInitLifeTotal,
		apDdSessInitLifePerMax,
                apDdSessInitLifeHigh,

--  Session Established Stats
                apDdSessEstablishedPeriodActive,
		apDdSessEstablishedPeriodHigh,
                apDdSessEstablishedPeriodTotal,
		apDdSessEstablishedLifeTotal,
		apDdSessEstablishedLifePerMax,
                apDdSessEstablishedLifeHigh,

--  Session Terminated Stats
                apDdSessTerminatedPeriodActive,
		apDdSessTerminatedPeriodHigh,
                apDdSessTerminatedPeriodTotal,
		apDdSessTerminatedLifeTotal,
		apDdSessTerminatedLifePerMax,
                apDdSessTerminatedLifeHigh,

--  Session Tiimeout Stats
                apDdSessTimeoutPeriodTotal,
		apDdSessTimeoutLifeTotal,
		apDdSessTimeoutLifePerMax,

--  Session Errors Stats
                apDdSessErrorsPeriodTotal,
		apDdSessErrorsLifeTotal,
		apDdSessErrorsLifePerMax,

--  Session Misses Stats
                apDdSessMissPeriodTotal,
		apDdSessMissLifeTotal,
		apDdSessMissLifePerMax,

--  Subscriber Stats
		apDdSubscriberPeriodActive,
		apDdSubscriberPeriodHigh,
                apDdSubscriberPeriodTotal,
		apDdSubscriberLifeTotal,
		apDdSubscriberLifePerMax,
                apDdSubscriberLifeHigh,

--  Subscribe Stats
                apDdSubscribePeriodActive,
		apDdSubscribePeriodHigh,
                apDdSubscribePeriodTotal,
		apDdSubscribeLifeTotal,
		apDdSubscribeLifePerMax,
                apDdSubscribeLifeHigh,

--  UnSubscribe Stats
                apDdUnsubscribePeriodActive,
		apDdUnsubscribePeriodHigh,
                apDdUnsubscribePeriodTotal,
		apDdUnsubscribeLifeTotal,
		apDdUnsubscribeLifePerMax,
                apDdUnsubscribeLifeHigh,

--  Subscriber Policy Hit Stats
                apDdPolicyHitPeriodActive,
		apDdPolicyHitPeriodHigh,
                apDdPolicyHitPeriodTotal,
		apDdPolicyHitLifeTotal,
		apDdPolicyHitLifePerMax,
                apDdPolicyHitLifeHigh,

--  Subscriber Policy Miss Stats
                apDdPolicyMissPeriodActive,
		apDdPolicyMissPeriodHigh,
                apDdPolicyMissPeriodTotal,
		apDdPolicyMissLifeTotal,
		apDdPolicyMissLifePerMax,
                apDdPolicyMissLifeHigh,

--  Subscriber Miss Stats
                apDdSubscriberMissPeriodTotal,
		apDdSubscriberMissLifeTotal,
		apDdSubscriberMissLifePerMax

	         }
      STATUS		current
      DESCRIPTION
	  "A collection of Session objects generic to DD system."
      ::= {  apDDObjectGroups 12 }

-- End of Session Stats Group


----------------------------------------------------
--
-- apDDNotificationGroups
--
----------------------------------------------------

apDDNotifObjectsGroup OBJECT-GROUP
     OBJECTS {
		apDdDiameterAgentHostName,
		apDdDiameterIPPort,
		apDdDiameterAgentOriginHostName,
		apDdDiameterAgentOriginRealmName,
		apDdTransportType,
		apDdInterfaceStatusReason

             }
     STATUS		current
     DESCRIPTION
	 "A collection of mib objects accessible only to traps."
      ::= { apDDNotificationGroups 1 }


apDDNotificationsGroup NOTIFICATION-GROUP
     NOTIFICATIONS {
               apDdConnectionFailureTrap,
	       apDdConnectionFailureClearTrap
	       }
     STATUS		current
      DESCRIPTION
	  "A collection of traps defined for DD."
      ::= { apDDNotificationGroups 2 }

apDDSCTPNotifObjectsGroup OBJECT-GROUP
        OBJECTS {
		apDdDiameterRemoteIPPort,
		apDdSCTPAssociationID,
		apDdSCTPIsPrimaryPath
                }
        STATUS  current
        DESCRIPTION
        "A collection of mib objects accessible only to SCTP path traps."
        ::= { apDDNotificationGroups 3 }

apDDSCTPNotificationsGroup NOTIFICATION-GROUP
        NOTIFICATIONS {
		apDdSCTPPathFailureTrap,
		apDdSCTPPathFailureClearTrap
                      }
        STATUS  current
        DESCRIPTION
        "A collection of traps defined for DD SCTP paths."
        ::= { apDDNotificationGroups 4 }

END
