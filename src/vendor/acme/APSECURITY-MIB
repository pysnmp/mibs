--ACMEPACKET-SECURITY-MIB:  Acme Packet SECURITY MIB file
--
--April 2008
--
--Copyright (c) by Oracle Communications
--All rights reserved.
--------------------------------------------------------------------------------
--This MIB provides a means to gather information about the
--Acme Management Interface running at the Net-Net SBC
--

APSECURITY-MIB DEFINITIONS ::= BEGIN

    IMPORTS
    MODULE-IDENTITY, OBJECT-TYPE, NOTIFICATION-TYPE, Integer32,
    IpAddress, Unsigned32, Counter32, Gauge32
        FROM SNMPv2-SMI
    OBJECT-GROUP, NOTIFICATION-GROUP
        FROM SNMPv2-CONF
    DisplayString, TruthValue
  	FROM SNMPv2-TC
    acmepacketMgmt
        FROM ACMEPACKET-SMI
    InetAddress, InetAddressType, InetPortNumber             
        FROM INET-ADDRESS-MIB;

    apSecurityModule MODULE-IDENTITY
        LAST-UPDATED	"201711240000Z"
        ORGANIZATION 	"Oracle Communications"
        CONTACT-INFO
			"           	Customer Service
		 	Postal:		Oracle Communications
					100 Crosby Drive 
					Bedford, MA 01730
					US
		    	Tel:		1-800-633-0738
			Url:		www.oracle.com
		 	E-mail:		support@oracle.com"
        DESCRIPTION     "The Net-Net SECURITY MIB for Oracle Communications Acme Packet SBCs"
        REVISION        "201207160000Z"
        DESCRIPTION     "Updated contact info"
	REVISION 	"201406260000Z" 			
        DESCRIPTION
	        "Updated Organization and Contact info."
        REVISION        "201710180000Z"
        DESCRIPTION     "Added apSecurityTacacsDownLocalAuthUsedTrap and
                        apSecurityTacacsDownLocalAuthUsedClearTrap notifications
                        and associated objects."
        REVISION        "201711240000Z"
        DESCRIPTION
                        "Added new MIB Definitions for Security Association (SA) Statistics."                       
        ::= { acmepacketMgmt 9 }

    apSecurityMIBObjects OBJECT IDENTIFIER ::= { apSecurityModule 1 }
    apSecuritySAMIBObjects OBJECT IDENTIFIER ::= { apSecurityModule 5 }

    apSecurityIPsecTunCount	OBJECT-TYPE
	SYNTAX         	Unsigned32
	UNITS		"tunnels"
      	MAX-ACCESS    	read-only
      	STATUS            current
      	DESCRIPTION
        	"The number of IPsec tunnels currently in progress."
	::= { apSecurityMIBObjects 1 }

    apSecurityIPsecTunCapPct    OBJECT-TYPE
	SYNTAX	    	Unsigned32 (0..100)
	UNITS		"%"
	MAX-ACCESS   	read-only
	STATUS          current
	DESCRIPTION
		"The percentage of licensed IPsec tunnels currently in progress."
	::= { apSecurityMIBObjects 2 }

    apSecurityIkeInterfaceStatsTable OBJECT-TYPE
        SYNTAX  	SEQUENCE OF ApSecurityIkeInterfaceStatsEntry
        MAX-ACCESS      not-accessible
        STATUS  	current
        DESCRIPTION
                "The table of Ike statistics per ike-interface for IKE negotiations."
        ::= { apSecurityMIBObjects 3 }
    apSecurityIkeInterfaceStatsEntry OBJECT-TYPE
        SYNTAX  	ApSecurityIkeInterfaceStatsEntry
        MAX-ACCESS      not-accessible
        STATUS  	current
        DESCRIPTION
                "IKE negotiation statistics for an IKE-interface."
        INDEX   { apSecurityIkeInterfaceType, apSecurityIkeInterfaceAddress }
        ::= { apSecurityIkeInterfaceStatsTable 1 }

    ApSecurityIkeInterfaceStatsEntry ::=
        SEQUENCE {
	        apSecurityIkeInterfaceType		        InetAddressType,
		apSecurityIkeInterfaceAddress			InetAddress,
		apSecurityIkeInterfaceCpuOverloadErrors		Unsigned32,
                apSecurityIkeInterfaceInitCookieErrors  	Unsigned32,
                apSecurityIkeInterfaceAuthErrors		Unsigned32,
		apSecurityIkeInterfaceEapAccessRequestErrors	Unsigned32,
                apSecurityIkeInterfaceEapAccessChallengeErrors	Unsigned32,
                apSecurityIkeInterfaceTsErrors			Unsigned32,
                apSecurityIkeInterfaceCpErrors			Unsigned32,
                apSecurityIkeInterfaceKeErrors			Unsigned32,
                apSecurityIkeInterfaceProposalErrors		Unsigned32,
		apSecurityIkeInterfaceSyntaxErrors		Unsigned32,
		apSecurityIkeInterfaceCriticalPayloadErrors	Unsigned32,
		apSecurityIkeInterfaceAuthFailureTca		Unsigned32,
		apSecurityIkeInterfaceTunnelRemovalsTca		Unsigned32,
		apSecurityIkeInterfaceDpdTca			Unsigned32,
        apSecurityIkeInterfaceEapOnlyNonZeroSPI     Unsigned32,
        apSecurityIkeInterfaceEapOnlyNonZeroProtoId     Unsigned32,
        apSecurityIkeInterfaceEapOnlyUnSupEapProto  Unsigned32,
        apSecurityIkeInterfaceIkeBadPortErrors  Counter32,
        apSecurityIkeInterfaceIkeBadAttrErrors  Counter32,
        apSecurityIkeInterfaceIkeBadCertErrors  Counter32,
        apSecurityIkeInterfaceIkeNoCertErrors  Counter32,
        apSecurityIkeInterfaceIkeBadCertTypeErrors  Counter32,
        apSecurityIkeInterfaceIkeBadCookieErrors  Counter32,
        apSecurityIkeInterfaceIkeBadCookie2Errors  Counter32,
        apSecurityIkeInterfaceIkeBadConfigErrors  Counter32,
        apSecurityIkeInterfaceIkeBadHashErrors  Counter32,
        apSecurityIkeInterfaceIkeBadIDErrors  Counter32,
        apSecurityIkeInterfaceIkeBadID2Errors  Counter32,
        apSecurityIkeInterfaceIkeBadKeErrors  Counter32,
        apSecurityIkeInterfaceIkeBadLenErrors  Counter32,
        apSecurityIkeInterfaceIkeBadMsgErrors  Counter32,
        apSecurityIkeInterfaceIkeBadMsgIdErrors  Counter32,
        apSecurityIkeInterfaceIkeBadNATDErrors  Counter32,
        apSecurityIkeInterfaceIkeBadNonceErrors  Counter32,
        apSecurityIkeInterfaceIkeBadNotifyCookieErrors  Counter32,
        apSecurityIkeInterfaceIkeBadPayloadErrors  Counter32,
        apSecurityIkeInterfaceIkeBadProposalErrors  Counter32,
        apSecurityIkeInterfaceIkeBadProtocolErrors  Counter32,
        apSecurityIkeInterfaceIkeBadSaErrors  Counter32,
        apSecurityIkeInterfaceIkeBadSigErrors  Counter32,
        apSecurityIkeInterfaceIkeBadSpiErrors  Counter32,
        apSecurityIkeInterfaceIkeBadVersionErrors  Counter32,
        apSecurityIkeInterfaceIkeBadXchgErrors  Counter32,
        apSecurityIkeInterfaceIkeBufferOverflowErrors  Counter32,
        apSecurityIkeInterfaceIkeConfigErrors  Counter32,
        apSecurityIkeInterfaceIkeGetSaFailErrors  Counter32,
        apSecurityIkeInterfaceIkeNewSaFailErrors  Counter32,
        apSecurityIkeInterfaceIkeNotifyPayloadErrors  Counter32,
        apSecurityIkeInterfaceIkeNullPSKErrors  Counter32,
        apSecurityIkeInterfaceIkeMismatchErrors  Counter32,
        apSecurityIkeInterfaceIkeMismatchAuthAlgoErrors  Counter32,
        apSecurityIkeInterfaceIkeMismatchAuthMethodErrors  Counter32,
        apSecurityIkeInterfaceIkeMismatchDHGroupErrors  Counter32,
        apSecurityIkeInterfaceIkeMismatchEncrAlgoErrors  Counter32,
        apSecurityIkeInterfaceIkeMismatchKeyLenErrors  Counter32,
        apSecurityIkeInterfaceCertInvalidStructErrors  Counter32,
        apSecurityIkeInterfaceCertNotExpectedOIDErrors  Counter32,
        apSecurityIkeInterfaceCertRsaExponentTooBigErrors  Counter32,
        apSecurityIkeInterfaceCertExpiredErrors  Counter32,
        apSecurityIkeInterfaceCertInvalidParentCertificateErrors Counter32,
        apSecurityIkeInterfaceCertUnsupportedDigestErrors  Counter32,
        apSecurityIkeInterfaceCertDNEStringTooLongErrors  Counter32,
        apSecurityIkeInterfaceCertStackOverflowErrors  Counter32,
        apSecurityIkeInterfaceCertKeyUsageMissingErrors  Counter32,
        apSecurityIkeInterfaceCertUnknownCriticalExtensionErrors  Counter32,
        apSecurityIkeInterfaceCertUnSupportedSignatureAlgoErrors  Counter32,
        apSecurityIkeInterfaceCertRSAModulusTooBigErrors  Counter32,
        apSecurityIkeInterfaceEapInstanceIdNotFoundErrors  Counter32,
        apSecurityIkeInterfaceEapInvalidPktSizeErrors  Counter32,
        apSecurityIkeInterfaceEapInvalidMethodTypeErrors  Counter32,
        apSecurityIkeInterfaceEapInvalidCodeErrors  Counter32,
        apSecurityIkeInterfaceEapInvalidPktErrors  Counter32,
        apSecurityIkeInterfaceAuthUserUnknownErrors Counter32,
        apSecurityIkeInterfaceAuthPlmnNotAllowedErrors Counter32,
        apSecurityIkeInterfaceAuthNon3GppAccessToEpcNotAllowedErrors Counter32,
        apSecurityIkeInterfaceAuthNoApnSubscriptionErrors Counter32,
        apSecurityIkeInterfaceAuthRatTypeNotAllowedErrors Counter32,
        apSecurityIkeInterfaceAuthAuthorizationRejectedErrors Counter32,
        apSecurityIkeInterfaceAuthNetworkFailureErrors Counter32,
        apSecurityIkeInterfaceIkeSaCapacityExceedCount Counter32,
        apSecurityIkeInterfaceIpsecSaCapacityExceedCount Counter32
		}

    apSecurityIkeInterfaceType OBJECT-TYPE
        SYNTAX		InetAddressType
        MAX-ACCESS	read-only
        STATUS		current
        DESCRIPTION
                "IPAddress type of the IKE-interface"
        ::= { apSecurityIkeInterfaceStatsEntry 1 }

    apSecurityIkeInterfaceAddress OBJECT-TYPE
        SYNTAX		InetAddress
        MAX-ACCESS	read-only
        STATUS		current
        DESCRIPTION
                "IPAddress of  the IKE-interface"
        ::= { apSecurityIkeInterfaceStatsEntry 2 }

    apSecurityIkeInterfaceCpuOverloadErrors OBJECT-TYPE
        SYNTAX		Unsigned32
        MAX-ACCESS	read-only
        STATUS		current
        DESCRIPTION
                "The count of CPU overload rejections on the IKE-interface"
        ::= { apSecurityIkeInterfaceStatsEntry 3 }

    apSecurityIkeInterfaceInitCookieErrors OBJECT-TYPE
        SYNTAX		Unsigned32
        MAX-ACCESS	read-only
        STATUS		current
        DESCRIPTION
                "The count of IKE COOKIE errors on the IKE-interface"
        ::= { apSecurityIkeInterfaceStatsEntry 4 }

    apSecurityIkeInterfaceAuthErrors OBJECT-TYPE
        SYNTAX		Unsigned32
        MAX-ACCESS	read-only
        STATUS		current
        DESCRIPTION
                "The count of IKE AUTH payload errors on the IKE-interface"
        ::= { apSecurityIkeInterfaceStatsEntry 5 }

    apSecurityIkeInterfaceEapAccessRequestErrors OBJECT-TYPE
        SYNTAX		Unsigned32
        MAX-ACCESS	read-only
        STATUS		current
        DESCRIPTION
                "The count of IKE EAP access request errors on the IKE-interface"
        ::= { apSecurityIkeInterfaceStatsEntry 6 }

    apSecurityIkeInterfaceEapAccessChallengeErrors OBJECT-TYPE
        SYNTAX		Unsigned32
        MAX-ACCESS	read-only
        STATUS		current
        DESCRIPTION
                "The count of IKE EAP access challenge errors on the IKE-interface"
        ::= { apSecurityIkeInterfaceStatsEntry 7 }

    apSecurityIkeInterfaceTsErrors OBJECT-TYPE
        SYNTAX		Unsigned32
        MAX-ACCESS	read-only
        STATUS		current
        DESCRIPTION
                "The count of IKE TS errors on the IKE-interface"
        ::= { apSecurityIkeInterfaceStatsEntry 8 }

    apSecurityIkeInterfaceCpErrors OBJECT-TYPE
        SYNTAX		Unsigned32
        MAX-ACCESS	read-only
        STATUS		current
        DESCRIPTION
                "The count of IKE config payload errors on the IKE-interface"
        ::= { apSecurityIkeInterfaceStatsEntry 9 }

    apSecurityIkeInterfaceKeErrors OBJECT-TYPE
        SYNTAX		Unsigned32
        MAX-ACCESS	read-only
        STATUS		current
        DESCRIPTION
                "The count of IKE KE errors on the IKE-interface"
        ::= { apSecurityIkeInterfaceStatsEntry 10 }

    apSecurityIkeInterfaceProposalErrors OBJECT-TYPE
        SYNTAX		Unsigned32
        MAX-ACCESS	read-only
        STATUS		current
        DESCRIPTION
                "The count of IKE proposal payload errors on the IKE-interface"
        ::= { apSecurityIkeInterfaceStatsEntry 11 }

    apSecurityIkeInterfaceSyntaxErrors OBJECT-TYPE
        SYNTAX		Unsigned32
        MAX-ACCESS	read-only
        STATUS		current
        DESCRIPTION
                "The count of IKE Syntax errors on the IKE-interface"
        ::= { apSecurityIkeInterfaceStatsEntry 12 }

    apSecurityIkeInterfaceCriticalPayloadErrors OBJECT-TYPE
        SYNTAX		Unsigned32
        MAX-ACCESS	read-only
        STATUS		current
        DESCRIPTION
                "The count of IKE critical payload errors on the IKE-interface"
        ::= { apSecurityIkeInterfaceStatsEntry 13 }

    apSecurityIkeInterfaceAuthFailureTca OBJECT-TYPE
        SYNTAX		Unsigned32
        MAX-ACCESS	read-only
        STATUS		current
        DESCRIPTION
                "Dummy object for the IKE authentication failure TCA"
        ::= { apSecurityIkeInterfaceStatsEntry 14 }

    apSecurityIkeInterfaceTunnelRemovalsTca OBJECT-TYPE
        SYNTAX		Unsigned32
        MAX-ACCESS	read-only
        STATUS		current
        DESCRIPTION
                "Dummy object for the IPsec tunnel removals TCA"
        ::= { apSecurityIkeInterfaceStatsEntry 15 }

    apSecurityIkeInterfaceDpdTca OBJECT-TYPE
        SYNTAX		Unsigned32
        MAX-ACCESS	read-only
        STATUS		current
        DESCRIPTION
                "Dummy object for the IKE dead peer detection TCA"
        ::= { apSecurityIkeInterfaceStatsEntry 16 }

    apSecurityIkeInterfaceEapOnlyNonZeroSPI OBJECT-TYPE
        SYNTAX		Unsigned32
        MAX-ACCESS	read-only
        STATUS		current
        DESCRIPTION
                "The count of Non Zero SPI in EAP-ONLY notification on the IKE-interface"
        ::= { apSecurityIkeInterfaceStatsEntry 17 }

    apSecurityIkeInterfaceEapOnlyNonZeroProtoId OBJECT-TYPE
        SYNTAX		Unsigned32
        MAX-ACCESS	read-only
        STATUS		current
        DESCRIPTION
                "The count of Non Zero ProtoId in EAP-ONLY notification on the IKE-interface"
        ::= { apSecurityIkeInterfaceStatsEntry 18 }

    apSecurityIkeInterfaceEapOnlyUnSupEapProto OBJECT-TYPE
        SYNTAX		Unsigned32
        MAX-ACCESS	read-only
        STATUS		current
        DESCRIPTION
                "The count of Unsupported EAP method in EAP-ONLY authentication on the IKE-interface"
        ::= { apSecurityIkeInterfaceStatsEntry 19 }

   apSecurityIkeInterfaceIkeBadPortErrors OBJECT-TYPE
        SYNTAX		Counter32
        MAX-ACCESS	read-only
        STATUS		current
        DESCRIPTION
                "The count of bad port errors on the IKE-interface"
        ::= { apSecurityIkeInterfaceStatsEntry 20 }

   apSecurityIkeInterfaceIkeBadAttrErrors OBJECT-TYPE
        SYNTAX		Counter32
        MAX-ACCESS	read-only
        STATUS		current
        DESCRIPTION
                "The count of bad IKE attribute errors on IKE-interface"
        ::= { apSecurityIkeInterfaceStatsEntry 21 }

   apSecurityIkeInterfaceIkeBadCertErrors OBJECT-TYPE
        SYNTAX		Counter32
        MAX-ACCESS	read-only
        STATUS		current
        DESCRIPTION
                "The count of bad certificate errors on the IKE-interface"
        ::= { apSecurityIkeInterfaceStatsEntry 22 }

   apSecurityIkeInterfaceIkeNoCertErrors OBJECT-TYPE
        SYNTAX		Counter32
        MAX-ACCESS	read-only
        STATUS		current
        DESCRIPTION
                "The count of missing user certificate errors on the IKE-interface"
        ::= { apSecurityIkeInterfaceStatsEntry 23 }

   apSecurityIkeInterfaceIkeBadCertTypeErrors OBJECT-TYPE
        SYNTAX		Counter32
        MAX-ACCESS	read-only
        STATUS		current
        DESCRIPTION
                "The count of bad certificate type errors on the IKE-interface"
        ::= { apSecurityIkeInterfaceStatsEntry 24 }

   apSecurityIkeInterfaceIkeBadCookieErrors OBJECT-TYPE
        SYNTAX		Counter32
        MAX-ACCESS	read-only
        STATUS		current
        DESCRIPTION
                "The count of bad cookie errors on IKE-interface"
        ::= { apSecurityIkeInterfaceStatsEntry 25 }

   apSecurityIkeInterfaceIkeBadCookie2Errors OBJECT-TYPE
        SYNTAX		Counter32
        MAX-ACCESS	read-only
        STATUS		current
        DESCRIPTION
                "The count of bad cookie2 errors on IKE-interface"
        ::= { apSecurityIkeInterfaceStatsEntry 26 }

   apSecurityIkeInterfaceIkeBadConfigErrors OBJECT-TYPE
        SYNTAX		Counter32
        MAX-ACCESS	read-only
        STATUS		current
        DESCRIPTION
                "The count of bad configuration payload errors on IKE-interface"
        ::= { apSecurityIkeInterfaceStatsEntry 27 }

   apSecurityIkeInterfaceIkeBadHashErrors OBJECT-TYPE
        SYNTAX		Counter32
        MAX-ACCESS	read-only
        STATUS		current
        DESCRIPTION
                "The count of incorrect PSK or Key ID errors on IKE-interface"
        ::= { apSecurityIkeInterfaceStatsEntry 28 }

   apSecurityIkeInterfaceIkeBadIDErrors OBJECT-TYPE
        SYNTAX		Counter32
        MAX-ACCESS	read-only
        STATUS		current
        DESCRIPTION
                "The count of bad ID payload errors on IKE-interface"
        ::= { apSecurityIkeInterfaceStatsEntry 29 }

   apSecurityIkeInterfaceIkeBadID2Errors OBJECT-TYPE
        SYNTAX		Counter32
        MAX-ACCESS	read-only
        STATUS		current
        DESCRIPTION
                "The count of bad ID or TS payload errors on IKE-interface"
        ::= { apSecurityIkeInterfaceStatsEntry 30 }

   apSecurityIkeInterfaceIkeBadKeErrors OBJECT-TYPE
        SYNTAX		Counter32
        MAX-ACCESS	read-only
        STATUS		current
        DESCRIPTION
                "The count of invalid or missing KE Payload errors on IKE-interface"
        ::= { apSecurityIkeInterfaceStatsEntry 31 }

   apSecurityIkeInterfaceIkeBadLenErrors OBJECT-TYPE
        SYNTAX		Counter32
        MAX-ACCESS	read-only
        STATUS		current
        DESCRIPTION
                "The count of bad message length errors on IKE-interface"
        ::= { apSecurityIkeInterfaceStatsEntry 32 }

   apSecurityIkeInterfaceIkeBadMsgErrors OBJECT-TYPE
        SYNTAX		Counter32
        MAX-ACCESS	read-only
        STATUS		current
        DESCRIPTION
                "The count of bad message errors on IKE-interface"
        ::= { apSecurityIkeInterfaceStatsEntry 33 }

   apSecurityIkeInterfaceIkeBadMsgIdErrors OBJECT-TYPE
        SYNTAX		Counter32
        MAX-ACCESS	read-only
        STATUS		current
        DESCRIPTION
                "The count of bad message id errors on IKE-interface"
        ::= { apSecurityIkeInterfaceStatsEntry 34 }

   apSecurityIkeInterfaceIkeBadNATDErrors OBJECT-TYPE
        SYNTAX		Counter32
        MAX-ACCESS	read-only
        STATUS		current
        DESCRIPTION
                "The count of unexpected or missing NAT-D Notify Payload errors on IKE-interface"
        ::= { apSecurityIkeInterfaceStatsEntry 35 }

   apSecurityIkeInterfaceIkeBadNonceErrors OBJECT-TYPE
        SYNTAX		Counter32
        MAX-ACCESS	read-only
        STATUS		current
        DESCRIPTION
                "The count of bad nonce value errors on IKE-interface"
        ::= { apSecurityIkeInterfaceStatsEntry 36 }

   apSecurityIkeInterfaceIkeBadNotifyCookieErrors OBJECT-TYPE
        SYNTAX		Counter32
        MAX-ACCESS	read-only
        STATUS		current
        DESCRIPTION
                "The count of bad notify cookie value errors on IKE-interface"
        ::= { apSecurityIkeInterfaceStatsEntry 37 }

   apSecurityIkeInterfaceIkeBadPayloadErrors OBJECT-TYPE
        SYNTAX		Counter32
        MAX-ACCESS	read-only
        STATUS		current
        DESCRIPTION
                "The count of bad payload errors on IKE-interface"
        ::= { apSecurityIkeInterfaceStatsEntry 38 }

   apSecurityIkeInterfaceIkeBadProposalErrors OBJECT-TYPE
        SYNTAX		Counter32
        MAX-ACCESS	read-only
        STATUS		current
        DESCRIPTION
                "The count of bad proposal errors on IKE-interface"
        ::= { apSecurityIkeInterfaceStatsEntry 39 }

   apSecurityIkeInterfaceIkeBadProtocolErrors OBJECT-TYPE
        SYNTAX		Counter32
        MAX-ACCESS	read-only
        STATUS		current
        DESCRIPTION
                "The count of bad protocol errors on IKE-interface"
        ::= { apSecurityIkeInterfaceStatsEntry 40 }

   apSecurityIkeInterfaceIkeBadSaErrors OBJECT-TYPE
        SYNTAX		Counter32
        MAX-ACCESS	read-only
        STATUS		current
        DESCRIPTION
                "The count of bad security association errors on IKE-interface"
        ::= { apSecurityIkeInterfaceStatsEntry 41 }

   apSecurityIkeInterfaceIkeBadSigErrors OBJECT-TYPE
        SYNTAX		Counter32
        MAX-ACCESS	read-only
        STATUS		current
        DESCRIPTION
                "The count of bad signature errors on IKE-interface"
        ::= { apSecurityIkeInterfaceStatsEntry 42 }

   apSecurityIkeInterfaceIkeBadSpiErrors OBJECT-TYPE
        SYNTAX		Counter32
        MAX-ACCESS	read-only
        STATUS		current
        DESCRIPTION
                "The count of bad Security Parameter Index errors on IKE-interface"
        ::= { apSecurityIkeInterfaceStatsEntry 43 }

   apSecurityIkeInterfaceIkeBadVersionErrors OBJECT-TYPE
        SYNTAX		Counter32
        MAX-ACCESS	read-only
        STATUS		current
        DESCRIPTION
                "The count of bad ike version errors on IKE-interface"
        ::= { apSecurityIkeInterfaceStatsEntry 44 }

   apSecurityIkeInterfaceIkeBadXchgErrors OBJECT-TYPE
        SYNTAX		Counter32
        MAX-ACCESS	read-only
        STATUS		current
        DESCRIPTION
                "The count of bad XCHG value errors on IKE-interface"
        ::= { apSecurityIkeInterfaceStatsEntry 45 }

   apSecurityIkeInterfaceIkeBufferOverflowErrors OBJECT-TYPE
        SYNTAX		Counter32
        MAX-ACCESS	read-only
        STATUS		current
        DESCRIPTION
                "The count of buffer overflow errors on IKE-interface"
        ::= { apSecurityIkeInterfaceStatsEntry 46 }

   apSecurityIkeInterfaceIkeConfigErrors OBJECT-TYPE
        SYNTAX		Counter32
        MAX-ACCESS	read-only
        STATUS		current
        DESCRIPTION
                "The count of configuration errors on IKE-interface"
        ::= { apSecurityIkeInterfaceStatsEntry 47 }

   apSecurityIkeInterfaceIkeGetSaFailErrors OBJECT-TYPE
        SYNTAX		Counter32
        MAX-ACCESS	read-only
        STATUS		current
        DESCRIPTION
                "The count of get security association errors on IKE-interface"
        ::= { apSecurityIkeInterfaceStatsEntry 48 }

   apSecurityIkeInterfaceIkeNewSaFailErrors OBJECT-TYPE
        SYNTAX		Counter32
        MAX-ACCESS	read-only
        STATUS		current
        DESCRIPTION
                "The count of new security association failures on IKE-interface"
        ::= { apSecurityIkeInterfaceStatsEntry 49 }

   apSecurityIkeInterfaceIkeNotifyPayloadErrors OBJECT-TYPE
        SYNTAX		Counter32
        MAX-ACCESS	read-only
        STATUS		current
        DESCRIPTION
                "The count of server reported failures on IKE-interface"
        ::= { apSecurityIkeInterfaceStatsEntry 50 }

   apSecurityIkeInterfaceIkeNullPSKErrors OBJECT-TYPE
        SYNTAX		Counter32
        MAX-ACCESS	read-only
        STATUS		current
        DESCRIPTION
                "The count of missing pre-shared key errors on IKE-interface"
        ::= { apSecurityIkeInterfaceStatsEntry 51 }

   apSecurityIkeInterfaceIkeMismatchErrors OBJECT-TYPE
        SYNTAX		Counter32
        MAX-ACCESS	read-only
        STATUS		current
        DESCRIPTION
                "The count of general proposal mismatchs on IKE-interface"
        ::= { apSecurityIkeInterfaceStatsEntry 52 }

   apSecurityIkeInterfaceIkeMismatchAuthAlgoErrors OBJECT-TYPE
        SYNTAX		Counter32
        MAX-ACCESS	read-only
        STATUS		current
        DESCRIPTION
                "The count of integrity algorithm mismatchs on IKE-interface"
        ::= { apSecurityIkeInterfaceStatsEntry 53 }

   apSecurityIkeInterfaceIkeMismatchAuthMethodErrors OBJECT-TYPE
        SYNTAX		Counter32
        MAX-ACCESS	read-only
        STATUS		current
        DESCRIPTION
                "The count of authentication methods mismatchs on IKE-interface"
        ::= { apSecurityIkeInterfaceStatsEntry 54 }

   apSecurityIkeInterfaceIkeMismatchDHGroupErrors OBJECT-TYPE
        SYNTAX		Counter32
        MAX-ACCESS	read-only
        STATUS		current
        DESCRIPTION
                "The count of DH group mismatchs on IKE-interface"
        ::= { apSecurityIkeInterfaceStatsEntry 55 }

   apSecurityIkeInterfaceIkeMismatchEncrAlgoErrors OBJECT-TYPE
        SYNTAX		Counter32
        MAX-ACCESS	read-only
        STATUS		current
        DESCRIPTION
                "The count of encryption algorithm mismatchs on IKE-interface"
        ::= { apSecurityIkeInterfaceStatsEntry 56 }

   apSecurityIkeInterfaceIkeMismatchKeyLenErrors OBJECT-TYPE
        SYNTAX		Counter32
        MAX-ACCESS	read-only
        STATUS		current
        DESCRIPTION
                "The count of key length mismatchs on IKE-interface"
        ::= { apSecurityIkeInterfaceStatsEntry 57 }

   apSecurityIkeInterfaceCertInvalidStructErrors OBJECT-TYPE
        SYNTAX		Counter32
        MAX-ACCESS	read-only
        STATUS		current
        DESCRIPTION
                "The count of malformed certificate errors on the IKE-interface"
        ::= { apSecurityIkeInterfaceStatsEntry 58 }

   apSecurityIkeInterfaceCertNotExpectedOIDErrors OBJECT-TYPE
        SYNTAX		Counter32
        MAX-ACCESS	read-only
        STATUS		current
        DESCRIPTION
                "The count of OID did not match expectations errors on the IKE-interface"
        ::= { apSecurityIkeInterfaceStatsEntry 59 }

   apSecurityIkeInterfaceCertRsaExponentTooBigErrors OBJECT-TYPE
        SYNTAX		Counter32
        MAX-ACCESS	read-only
        STATUS		current
        DESCRIPTION
                "The count of RSA exponent was too big errors on the IKE-interface"
        ::= { apSecurityIkeInterfaceStatsEntry 60 }


   apSecurityIkeInterfaceCertExpiredErrors OBJECT-TYPE
        SYNTAX		Counter32
        MAX-ACCESS	read-only
        STATUS		current
        DESCRIPTION
                "The count of Server Certificate expired errors on the IKE-interface"
        ::= { apSecurityIkeInterfaceStatsEntry 61 }


   apSecurityIkeInterfaceCertInvalidParentCertificateErrors OBJECT-TYPE
        SYNTAX		Counter32
        MAX-ACCESS	read-only
        STATUS		current
        DESCRIPTION
                "The count of Server Certificates which cannot be verified errors on the IKE-interface"
        ::= { apSecurityIkeInterfaceStatsEntry 62 }


   apSecurityIkeInterfaceCertUnsupportedDigestErrors OBJECT-TYPE
        SYNTAX		Counter32
        MAX-ACCESS	read-only
        STATUS		current
        DESCRIPTION
                "The count of unsupported digest type errors on the IKE-interface"
        ::= { apSecurityIkeInterfaceStatsEntry 63 }


   apSecurityIkeInterfaceCertDNEStringTooLongErrors OBJECT-TYPE
        SYNTAX		Counter32
        MAX-ACCESS	read-only
        STATUS		current
        DESCRIPTION
                "The count of distinguished Name element string too long errors on the IKE-interface"
        ::= { apSecurityIkeInterfaceStatsEntry 64 }


   apSecurityIkeInterfaceCertStackOverflowErrors OBJECT-TYPE
        SYNTAX		Counter32
        MAX-ACCESS	read-only
        STATUS		current
        DESCRIPTION
                "The count of certificate stack overflow errors on the IKE-interface"
        ::= { apSecurityIkeInterfaceStatsEntry 65 }


   apSecurityIkeInterfaceCertKeyUsageMissingErrors OBJECT-TYPE
        SYNTAX		Counter32
        MAX-ACCESS	read-only
        STATUS		current
        DESCRIPTION
                "The count of certificate key usage information missing errors on the IKE-interface"
        ::= { apSecurityIkeInterfaceStatsEntry 66 }


   apSecurityIkeInterfaceCertUnknownCriticalExtensionErrors OBJECT-TYPE
        SYNTAX		Counter32
        MAX-ACCESS	read-only
        STATUS		current
        DESCRIPTION
                "The count of certificate unknown critical extension errors on the IKE-interface"
        ::= { apSecurityIkeInterfaceStatsEntry 67 }


   apSecurityIkeInterfaceCertUnSupportedSignatureAlgoErrors OBJECT-TYPE
        SYNTAX		Counter32
        MAX-ACCESS	read-only
        STATUS		current
        DESCRIPTION
                "The count of unsupported signature algorithm errors on the IKE-interface"
        ::= { apSecurityIkeInterfaceStatsEntry 68 }


   apSecurityIkeInterfaceCertRSAModulusTooBigErrors OBJECT-TYPE
        SYNTAX		Counter32
        MAX-ACCESS	read-only
        STATUS		current
        DESCRIPTION
                "The count of RSA modulus value too large errors on the IKE-interface"
        ::= { apSecurityIkeInterfaceStatsEntry 69 }


   apSecurityIkeInterfaceEapInstanceIdNotFoundErrors OBJECT-TYPE
        SYNTAX		Counter32
        MAX-ACCESS	read-only
        STATUS		current
        DESCRIPTION
                "The count of EAP instance ID not found errors on the IKE-interface"
        ::= { apSecurityIkeInterfaceStatsEntry 70 }


   apSecurityIkeInterfaceEapInvalidPktSizeErrors OBJECT-TYPE
        SYNTAX		Counter32
        MAX-ACCESS	read-only
        STATUS		current
        DESCRIPTION
                "The count of EAP packet size invalid errors on the IKE-interface"
        ::= { apSecurityIkeInterfaceStatsEntry 71 }

   apSecurityIkeInterfaceEapInvalidMethodTypeErrors OBJECT-TYPE
        SYNTAX		Counter32
        MAX-ACCESS	read-only
        STATUS		current
        DESCRIPTION
                "The count of EAP method type invalid errors on the IKE-interface"
        ::= { apSecurityIkeInterfaceStatsEntry 72 }


   apSecurityIkeInterfaceEapInvalidCodeErrors OBJECT-TYPE
        SYNTAX		Counter32
        MAX-ACCESS	read-only
        STATUS		current
        DESCRIPTION
                "The count of EAP code invalid errors on the IKE-interface"
        ::= { apSecurityIkeInterfaceStatsEntry 73 }


   apSecurityIkeInterfaceEapInvalidPktErrors OBJECT-TYPE
        SYNTAX		Counter32
        MAX-ACCESS	read-only
        STATUS		current
        DESCRIPTION
                "The count of EAP packet invalid errors on the IKE-interface"
        ::= { apSecurityIkeInterfaceStatsEntry 74 }

   apSecurityIkeInterfaceAuthUserUnknownErrors OBJECT-TYPE
        SYNTAX		Counter32
        MAX-ACCESS	read-only
        STATUS		current
        DESCRIPTION
                "The count of User Unknown authentication errors on the IKE-interface"
        ::= { apSecurityIkeInterfaceStatsEntry 75 }

   apSecurityIkeInterfaceAuthPlmnNotAllowedErrors OBJECT-TYPE
        SYNTAX		Counter32
        MAX-ACCESS	read-only
        STATUS		current
        DESCRIPTION
                "The count of PLMN not allowed authentication errors on the IKE-interface"
        ::= { apSecurityIkeInterfaceStatsEntry 76 }

   apSecurityIkeInterfaceAuthNon3GppAccessToEpcNotAllowedErrors OBJECT-TYPE
        SYNTAX		Counter32
        MAX-ACCESS	read-only
        STATUS		current
        DESCRIPTION
                "The count of Non 3gpp access to EPC not allowed authentication errors on the IKE-interface"
        ::= { apSecurityIkeInterfaceStatsEntry 77 }

   apSecurityIkeInterfaceAuthNoApnSubscriptionErrors OBJECT-TYPE
        SYNTAX		Counter32
        MAX-ACCESS	read-only
        STATUS		current
        DESCRIPTION
                "The count of No APN subscription authentication errors on the IKE-interface"
        ::= { apSecurityIkeInterfaceStatsEntry 78 }

   apSecurityIkeInterfaceAuthRatTypeNotAllowedErrors OBJECT-TYPE
        SYNTAX		Counter32
        MAX-ACCESS	read-only
        STATUS		current
        DESCRIPTION
                "The count of RAT type not allowed authentication errors on the IKE-interface"
        ::= { apSecurityIkeInterfaceStatsEntry 79 }

   apSecurityIkeInterfaceAuthAuthorizationRejectedErrors OBJECT-TYPE
        SYNTAX		Counter32
        MAX-ACCESS	read-only
        STATUS		current
        DESCRIPTION
                "The count of Authorization Rejected authentication errors on the IKE-interface"
        ::= { apSecurityIkeInterfaceStatsEntry 80 }

   apSecurityIkeInterfaceAuthNetworkFailureErrors OBJECT-TYPE
        SYNTAX		Counter32
        MAX-ACCESS	read-only
        STATUS		current
        DESCRIPTION
                "The count of Network Failure authentication errors on the IKE-interface"
        ::= { apSecurityIkeInterfaceStatsEntry 81 }

    apSecurityIkeInterfaceIkeSaCapacityExceedCount OBJECT-TYPE
        SYNTAX      Counter32
        MAX-ACCESS  read-only
        STATUS      current
        DESCRIPTION
                "The count of number of times we excceded IKE SA capacity"
        ::= { apSecurityIkeInterfaceStatsEntry 82 }

    apSecurityIkeInterfaceIpsecSaCapacityExceedCount OBJECT-TYPE
        SYNTAX      Counter32
        MAX-ACCESS  read-only
        STATUS      current
        DESCRIPTION
                "The count of number of times we excceded IPSEC SA capacity"
        ::= { apSecurityIkeInterfaceStatsEntry 83 }

    apSecurityTacacsTable OBJECT-TYPE
        SYNTAX  	SEQUENCE OF ApSecurityTacacsEntry
        MAX-ACCESS      not-accessible
        STATUS  	current
        DESCRIPTION
                "The table of all tacacs, including the system-wide
		consolidated license (always index 1)"
        ::= { apSecurityMIBObjects 4 }

    apSecurityTacacsEntry OBJECT-TYPE
        SYNTAX  	ApSecurityTacacsEntry
        MAX-ACCESS      not-accessible
        STATUS  	current
        DESCRIPTION
                "An entry in the table of all licenses"
        INDEX           { apSecurityTacacsIndex }
        ::= { apSecurityTacacsTable 1}


    ApSecurityTacacsEntry ::=
        SEQUENCE {
                apSecurityTacacsIndex                     Integer32 (1..2147483647),
                apSecurityTacacsServer	                  DisplayString,
                apSecurityTacacsCliCommands               Unsigned32,
                apSecurityTacacsSuccessAuthentication     Unsigned32,
                apSecurityTacacsFailureAuthentication     Unsigned32,
                apSecurityTacacsSuccessAuthorization      Unsigned32,
                apSecurityTacacsFailureAuthorization      Unsigned32
		}
	
    apSecurityTacacsIndex OBJECT-TYPE
        SYNTAX          Integer32 (1..2147483647)
        MAX-ACCESS      not-accessible
        STATUS          current
        DESCRIPTION     
                "Unique index for the tacacs table. "
        ::= { apSecurityTacacsEntry 1 }


    apSecurityTacacsServer OBJECT-TYPE
        SYNTAX             DisplayString (SIZE (0..255))
        MAX-ACCESS         read-only
        STATUS             current
        DESCRIPTION     
       		"Server for last transaction"   
        ::= { apSecurityTacacsEntry 2 }

    apSecurityTacacsCliCommands	OBJECT-TYPE
        SYNTAX          Unsigned32
	MAX-ACCESS      read-only
        STATUS          current
        DESCRIPTION     
                "Number of CLI commands sent for TACACS+ accounting"   
        ::= { apSecurityTacacsEntry 3 }

    apSecurityTacacsSuccessAuthentication OBJECT-TYPE
        SYNTAX          Unsigned32
	MAX-ACCESS      read-only
        STATUS          current
        DESCRIPTION     
                "Number of successful TACACS+ authentication requests"   
        ::= { apSecurityTacacsEntry 4 }

    apSecurityTacacsFailureAuthentication OBJECT-TYPE
        SYNTAX          Unsigned32
	MAX-ACCESS      read-only
        STATUS          current
        DESCRIPTION     
                "Number of failed TACACS+ authentication requests"   
        ::= { apSecurityTacacsEntry 5 }

    apSecurityTacacsSuccessAuthorization OBJECT-TYPE
        SYNTAX          Unsigned32
	MAX-ACCESS      read-only
        STATUS          current
        DESCRIPTION     
                "Number of successful TACACS+ authorization requests"   
        ::= { apSecurityTacacsEntry 6 }

    apSecurityTacacsFailureAuthorization OBJECT-TYPE
        SYNTAX          Unsigned32
	MAX-ACCESS      read-only
        STATUS          current
        DESCRIPTION     
                "Number of failed TACACS+ authorization requests"   
        ::= { apSecurityTacacsEntry 7 }

    apSecurityOCSRIpAddress 	OBJECT-TYPE
	SYNTAX		IpAddress
	MAX-ACCESS	accessible-for-notify
	STATUS		current
	DESCRIPTION
	    "OCSR server IP address."
	::= { apSecurityMIBObjects 5 }

    apSecurityOCSRHostname      OBJECT-TYPE
	SYNTAX        DisplayString
	MAX-ACCESS    accessible-for-notify
	STATUS	      current
	DESCRIPTION   "OCSR server hostname."
	::= { apSecurityMIBObjects 6 }

    apSecurityCrlIssuer      OBJECT-TYPE
	SYNTAX        DisplayString
	MAX-ACCESS    accessible-for-notify
	STATUS	      current
	DESCRIPTION   "CRL issuer name."
	::= { apSecurityMIBObjects 7 }

    apSecurityCspName      OBJECT-TYPE
	SYNTAX        DisplayString
	MAX-ACCESS    accessible-for-notify
	STATUS	      current
	DESCRIPTION   "Cert-status-profile object name for fetching the CRL. 
	               If the CRL is just loaded from local file, then it is 
		       specified as file"
	::= { apSecurityMIBObjects 8 }

    apSecurityIkeInterfaceInfoTable OBJECT-TYPE
        SYNTAX  	SEQUENCE OF ApSecurityIkeInterfaceInfoEntry
        MAX-ACCESS      not-accessible
        STATUS  	current
        DESCRIPTION
                "The table of Ike Info per ike-interface for IKE negotiations."
        ::= { apSecurityMIBObjects 9 }

    apSecurityIkeInterfaceInfoEntry OBJECT-TYPE
        SYNTAX  	ApSecurityIkeInterfaceInfoEntry
        MAX-ACCESS      not-accessible
        STATUS  	current
        DESCRIPTION     "IKE info for an IKE-interface."
        AUGMENTS	{ apSecurityIkeInterfaceStatsEntry }
        ::= { apSecurityIkeInterfaceInfoTable 1 }

    ApSecurityIkeInterfaceInfoEntry ::=
        SEQUENCE {
		apSecurityIkeInterfaceChildSaRequest		Unsigned32,
		apSecurityIkeInterfaceChildSaSuccess		Unsigned32,
		apSecurityIkeInterfaceChildSaFail		Unsigned32,
		apSecurityIkeInterfaceChildSaDelRequest		Unsigned32,
		apSecurityIkeInterfaceChildSaDelSuccess		Unsigned32,
		apSecurityIkeInterfaceChildSaDelFail		Unsigned32,
		apSecurityIkeInterfaceChildSaRekey		Unsigned32,
		apSecurityIkeInterfaceInitialChildSa		Unsigned32,
		apSecurityIkeInterfaceDPDRecvPortChange		Unsigned32,
		apSecurityIkeInterfaceDPDRecvIPChange		Unsigned32,
		apSecurityIkeInterfaceDPDRespRecv		Unsigned32,
		apSecurityIkeInterfaceDPDRespNotRecv		Unsigned32,
		apSecurityIkeInterfaceDPDRecv			Unsigned32,
		apSecurityIkeInterfaceDPDRetran			Unsigned32,
		apSecurityIkeInterfaceDPDSent			Unsigned32,
        apSecurityIkeInterfaceIKESAPacketSent		Unsigned32,
		apSecurityIkeInterfaceIKESAPacketRcv		Unsigned32,
		apSecurityIkeInterfaceIKESAPacketDropped	Unsigned32,
		apSecurityIkeInterfaceAuthFailure		Unsigned32,
		apSecurityIkeInterfaceMsgError			Unsigned32,
		apSecurityIkeInterfaceAuthIDError		Unsigned32,
		apSecurityIkeInterfaceAuthCertCheckRequest	Unsigned32,
		apSecurityIkeInterfaceAuthCertCheckSuccess	Unsigned32,
		apSecurityIkeInterfaceAuthCertCheckFailure	Unsigned32,
		apSecurityIkeInterfaceDDosSent			Unsigned32,
		apSecurityIkeInterfaceDDosRecv			Unsigned32,	
		apSecurityIkeInterfaceMessageRetrans		Unsigned32,
		apSecurityIkeInterfaceSAInitMsgRecv		Unsigned32,
		apSecurityIkeInterfaceSAInitMsgSent		Unsigned32,
		apSecurityIkeInterfaceSAEstablishmentAttempts	Unsigned32,
		apSecurityIkeInterfaceSAEstablishmentSuccess	Unsigned32,
		apSecurityIkeInterfaceTunnelRate			Unsigned32,
		apSecurityIkeInterfaceCurrentChildSaPair	Unsigned32,
		apSecurityIkeInterfaceBlacklistAuthIDError	Unsigned32,
        apSecurityIkeInterfaceRekeyOnSNoverflow     Unsigned32,
        apSecurityIkeInterfaceDPDFailSaDel      Unsigned32,
        apSecurityIkeInterfaceEapOnlyAuthentication     Unsigned32,
        apSecurityIkeInterfaceEapOnlyWithAuthPayload    Unsigned32,
                apSecurityIkeInterfaceEapSimSucc                 Counter32,
                apSecurityIkeInterfaceEapSimFail                 Counter32,
                apSecurityIkeInterfaceEapAkaSucc                 Counter32,
                apSecurityIkeInterfaceEapAkaFail                 Counter32,
                apSecurityIkeInterfaceEapAkaPrimeSucc            Counter32,
                apSecurityIkeInterfaceEapAkaPrimeFail            Counter32,
                apSecurityIkeInterfaceEapTlsSucc                 Counter32,
                apSecurityIkeInterfaceEapTlsFail                 Counter32,
                apSecurityIkeInterfaceEapTtlsSucc                Counter32,
                apSecurityIkeInterfaceEapTtlsFail                Counter32,
                apSecurityIkeInterfaceEapOtherSucc               Counter32 ,
                apSecurityIkeInterfaceEapOtherFail               Counter32,
        apSecurityIkeInterfaceNatKeepAliveMsgsRecv    Counter32,
        apSecurityIkeInterfaceBroadcastOrMulticastMsgcRecv    Counter32,
        apSecurityIkeInterfaceIkeSaAuthMsgsRecv    Counter32,
        apSecurityIkeInterfaceIkeSaAuthMsgsSent    Counter32,
        apSecurityIkeInterfaceIkeSaChildMsgsRecv    Counter32,
        apSecurityIkeInterfaceIkeSaChildMsgsSent    Counter32,
        apSecurityIkeInterfaceIkeSaInfoMsgsRecv    Counter32,
        apSecurityIkeInterfaceIkeSaInfoMsgsSent    Counter32,
        apSecurityIkeInterfaceInIkeSaRekeyRequest    Counter32,
        apSecurityIkeInterfaceInIkeSaRekeyRequestSuccess    Counter32,
        apSecurityIkeInterfaceInIkeSaRekeyRequestFailure    Counter32,
        apSecurityIkeInterfaceOutIkeSaRekeyRequest    Counter32,
        apSecurityIkeInterfaceOutIkeSaRekeyRequestSuccess    Counter32,
        apSecurityIkeInterfaceOutIkeSaRekeyRequestFailure    Counter32,
        apSecurityIkeInterfaceInIkeSaDeleteRequest    Counter32,
        apSecurityIkeInterfaceInIkeSaDeleteRequestSuccess    Counter32,
        apSecurityIkeInterfaceInIkeSaDeleteRequestFailure    Counter32,
        apSecurityIkeInterfaceOutIkeSaDeleteRequest    Counter32,
        apSecurityIkeInterfaceHalfOpenSecurityAssociations    Counter32,
        apSecurityIkeInterfaceIkeTunnelAvgHoldTime    Unsigned32,
        apSecurityIkeInterfaceIkeTunnelAvgSetupTime    Unsigned32,
        apSecurityIkeInterfaceMobikeSupportRequest      Counter32,
        apSecurityIkeInterfaceMobikeSupportResponse     Counter32,
        apSecurityIkeInterfaceMobikeUpdateSAAddrRcvd       Counter32,
        apSecurityIkeInterfaceMobikeUpdateSASuccess        Counter32,
        apSecurityIkeInterfaceMobikeUpdateSAAddrFamMismatch        Counter32,
        apSecurityIkeInterfaceMobikeUpdateSAFailUnexpUpdate        Counter32,
        apSecurityIkeInterfaceMobikeUpdateSASameAddress    Counter32,
        apSecurityIkeInterfaceMobikeUpdateSAFailInternal   Counter32,
        apSecurityIkeInterfaceMobikeReturnRouteCheckRequests Counter32,
        apSecurityIkeInterfaceMobikeFailToSendRouteCheck        Counter32,
        apSecurityIkeInterfaceMobikeReturnRouteCheckSuccess  Counter32,
        apSecurityIkeInterfaceMobikeReturnRouteCheckTimeout  Counter32,
        apSecurityIkeInterfaceMobikeRouteCheckFailSAdel   Counter32,
        apSecurityIkeInterfaceMobikeIntSaCommFailSaDel  Counter32,
        apSecurityIkeInterfaceMobikeMisMatchCookie2Errors       Counter32,
		apSecurityIkeInterfaceTunnelTearDownRate			Unsigned32
		}

    apSecurityIkeInterfaceChildSaRequest OBJECT-TYPE
        SYNTAX		Unsigned32
        MAX-ACCESS	read-only
        STATUS		current
        DESCRIPTION
                "Number of Child SA Requests on the IKE-interface."
        ::= { apSecurityIkeInterfaceInfoEntry 1 }
        
    apSecurityIkeInterfaceChildSaSuccess OBJECT-TYPE
        SYNTAX		Unsigned32
        MAX-ACCESS	read-only
        STATUS		current
        DESCRIPTION
                "Number of Child SA Success on the IKE-interface."
        ::= { apSecurityIkeInterfaceInfoEntry 2 }

    apSecurityIkeInterfaceChildSaFail OBJECT-TYPE
        SYNTAX		Unsigned32
        MAX-ACCESS	read-only
        STATUS		current
        DESCRIPTION
                "Number of Child SA Failures on the IKE-interface."
        ::= { apSecurityIkeInterfaceInfoEntry 3 }

    apSecurityIkeInterfaceChildSaDelRequest OBJECT-TYPE
        SYNTAX		Unsigned32
        MAX-ACCESS	read-only
        STATUS		current
        DESCRIPTION
                "Number of Child SA Delete Requests on the IKE-interface."
        ::= { apSecurityIkeInterfaceInfoEntry 4 }

    apSecurityIkeInterfaceChildSaDelSuccess OBJECT-TYPE
        SYNTAX		Unsigned32
        MAX-ACCESS	read-only
        STATUS		current
        DESCRIPTION
                "Number of Child SA Delete Success on the IKE-interface."
        ::= { apSecurityIkeInterfaceInfoEntry 5 }

    apSecurityIkeInterfaceChildSaDelFail OBJECT-TYPE
        SYNTAX		Unsigned32
        MAX-ACCESS	read-only
        STATUS		current
        DESCRIPTION
                "Number of Child SA Delete Failures on the IKE-interface."
        ::= { apSecurityIkeInterfaceInfoEntry 6 }

    apSecurityIkeInterfaceChildSaRekey OBJECT-TYPE
        SYNTAX		Unsigned32
        MAX-ACCESS	read-only
        STATUS		current
        DESCRIPTION
                "Number of Child SA Rekeys on the IKE-interface."
        ::= { apSecurityIkeInterfaceInfoEntry 7 }

    apSecurityIkeInterfaceInitialChildSa OBJECT-TYPE
        SYNTAX		Unsigned32
        MAX-ACCESS	read-only
        STATUS		current
        DESCRIPTION
                "Number of Initial Child SA Establishments on the IKE-interface."
        ::= { apSecurityIkeInterfaceInfoEntry 8 }

    apSecurityIkeInterfaceDPDRecvPortChange OBJECT-TYPE
        SYNTAX		Unsigned32
        MAX-ACCESS	read-only
        STATUS		current
        DESCRIPTION
                "Number of DPD Port Change Received on the IKE-interface."
        ::= { apSecurityIkeInterfaceInfoEntry 9 }

    apSecurityIkeInterfaceDPDRecvIPChange OBJECT-TYPE
        SYNTAX		Unsigned32
        MAX-ACCESS	read-only
        STATUS		current
        DESCRIPTION
                "Number of DPD IP Change Received on the IKE-interface."
        ::= { apSecurityIkeInterfaceInfoEntry 10 }

    apSecurityIkeInterfaceDPDRespRecv OBJECT-TYPE
        SYNTAX		Unsigned32
        MAX-ACCESS	read-only
        STATUS		current
        DESCRIPTION
                "Number of DPD Responses Received on the IKE-interface."
        ::= { apSecurityIkeInterfaceInfoEntry 11 }

    apSecurityIkeInterfaceDPDRespNotRecv OBJECT-TYPE
        SYNTAX		Unsigned32
        MAX-ACCESS	read-only
        STATUS		current
        DESCRIPTION
                "Number of DPD Responses Not Received on the IKE-interface."
        ::= { apSecurityIkeInterfaceInfoEntry 12 }

    apSecurityIkeInterfaceDPDRecv OBJECT-TYPE
        SYNTAX		Unsigned32
        MAX-ACCESS	read-only
        STATUS		current
        DESCRIPTION
                "Number of DPD Packets Received on the IKE-interface."
        ::= { apSecurityIkeInterfaceInfoEntry 13 }

    apSecurityIkeInterfaceDPDRetran OBJECT-TYPE
        SYNTAX		Unsigned32
        MAX-ACCESS	read-only
        STATUS		current
        DESCRIPTION
                "Number of DPD Packets Retransmitted on the IKE-interface."
        ::= { apSecurityIkeInterfaceInfoEntry 14 }

    apSecurityIkeInterfaceDPDSent OBJECT-TYPE
        SYNTAX		Unsigned32
        MAX-ACCESS	read-only
        STATUS		current
        DESCRIPTION
                "Number of DPD Packets Sent on the IKE-interface."
        ::= { apSecurityIkeInterfaceInfoEntry 15 }

    apSecurityIkeInterfaceIKESAPacketSent OBJECT-TYPE
        SYNTAX		Unsigned32
        MAX-ACCESS	read-only
        STATUS		current
        DESCRIPTION
                "Number of IKE SA Packets Sent on the IKE-interface."
        ::= { apSecurityIkeInterfaceInfoEntry 16 }

    apSecurityIkeInterfaceIKESAPacketRcv OBJECT-TYPE
        SYNTAX		Unsigned32
        MAX-ACCESS	read-only
        STATUS		current
        DESCRIPTION
                "Number of IKE SA Packets Received on the IKE-interface."
        ::= { apSecurityIkeInterfaceInfoEntry 17 }

    apSecurityIkeInterfaceIKESAPacketDropped OBJECT-TYPE
        SYNTAX		Unsigned32
        MAX-ACCESS	read-only
        STATUS		current
        DESCRIPTION
                "Number of IKE SA Packets dropped on the IKE-interface."
        ::= { apSecurityIkeInterfaceInfoEntry 18 }

    apSecurityIkeInterfaceAuthFailure OBJECT-TYPE
        SYNTAX		Unsigned32
        MAX-ACCESS	read-only
        STATUS		current
        DESCRIPTION
                "Number of Authentication Failures on the IKE-interface."
        ::= { apSecurityIkeInterfaceInfoEntry 19 }

    apSecurityIkeInterfaceMsgError OBJECT-TYPE
        SYNTAX		Unsigned32
        MAX-ACCESS	read-only
        STATUS		current
        DESCRIPTION
                "Number of IKE Message Errors on the IKE-interface."
        ::= { apSecurityIkeInterfaceInfoEntry 20 }

    apSecurityIkeInterfaceAuthIDError OBJECT-TYPE
        SYNTAX		Unsigned32
        MAX-ACCESS	read-only
        STATUS		current
        DESCRIPTION
                "Number of Authentication ID Errors on the IKE-interface."
        ::= { apSecurityIkeInterfaceInfoEntry 21 }

    apSecurityIkeInterfaceAuthCertCheckRequest OBJECT-TYPE
        SYNTAX		Unsigned32
        MAX-ACCESS	read-only
        STATUS		current
        DESCRIPTION
                "Number of Certificate Status Requests on the IKE-interface."
        ::= { apSecurityIkeInterfaceInfoEntry 22 }

    apSecurityIkeInterfaceAuthCertCheckSuccess OBJECT-TYPE
        SYNTAX		Unsigned32
        MAX-ACCESS	read-only
        STATUS		current
        DESCRIPTION
                "Number of Certificate Status Success on the IKE-interface."
        ::= { apSecurityIkeInterfaceInfoEntry 23 }

    apSecurityIkeInterfaceAuthCertCheckFailure OBJECT-TYPE
        SYNTAX		Unsigned32
        MAX-ACCESS	read-only
        STATUS		current
        DESCRIPTION
                "Number of Certificate Status Failures on the IKE-interface."
        ::= { apSecurityIkeInterfaceInfoEntry 24 }

    apSecurityIkeInterfaceDDosSent OBJECT-TYPE
        SYNTAX		Unsigned32
        MAX-ACCESS	read-only
        STATUS		current
        DESCRIPTION
                "Number of DDoS Sent on the IKE-interface."
        ::= { apSecurityIkeInterfaceInfoEntry 25 }

    apSecurityIkeInterfaceDDosRecv OBJECT-TYPE
        SYNTAX		Unsigned32
        MAX-ACCESS	read-only
        STATUS		current
        DESCRIPTION
                "Number of DDoS Received on the IKE-interface."
        ::= { apSecurityIkeInterfaceInfoEntry 26 }

    apSecurityIkeInterfaceMessageRetrans OBJECT-TYPE
        SYNTAX		Unsigned32
        MAX-ACCESS	read-only
        STATUS		current
        DESCRIPTION
                "Number of IKE Message Retransmissions on the IKE-interface."
        ::= { apSecurityIkeInterfaceInfoEntry 27 }


    apSecurityIkeInterfaceSAInitMsgRecv OBJECT-TYPE
        SYNTAX		Unsigned32
        MAX-ACCESS	read-only
        STATUS		current
        DESCRIPTION
                "Number of IKE_SA_INIT messages received on the IKE-interface."
        ::= { apSecurityIkeInterfaceInfoEntry 28 }

    apSecurityIkeInterfaceSAInitMsgSent OBJECT-TYPE
        SYNTAX		Unsigned32
        MAX-ACCESS	read-only
        STATUS		current
        DESCRIPTION
                "Number of IKE_SA_INIT messages sent on the IKE-interface."
        ::= { apSecurityIkeInterfaceInfoEntry 29 }

    apSecurityIkeInterfaceSAEstablishmentAttempts OBJECT-TYPE
        SYNTAX		Unsigned32
        MAX-ACCESS	read-only
        STATUS		current
        DESCRIPTION
                "Number of IKE_SA establishment attempts on the IKE-interface."
        ::= { apSecurityIkeInterfaceInfoEntry 30 }

    apSecurityIkeInterfaceSAEstablishmentSuccess OBJECT-TYPE
        SYNTAX		Unsigned32
        MAX-ACCESS	read-only
        STATUS		current
        DESCRIPTION
                "Number of IKE_SA establishment success on the IKE-interface."
        ::= { apSecurityIkeInterfaceInfoEntry 31 }

    apSecurityIkeInterfaceTunnelRate OBJECT-TYPE
        SYNTAX		Unsigned32
        MAX-ACCESS	read-only
        STATUS		current
        DESCRIPTION
                "Number of Tunnels per second averaged over 100sec window on the IKE-interface."
        ::= { apSecurityIkeInterfaceInfoEntry 32 }

    apSecurityIkeInterfaceCurrentChildSaPair OBJECT-TYPE

        SYNTAX		Unsigned32

        MAX-ACCESS	read-only

        STATUS		current

        DESCRIPTION

                "Current number of Child Security Association Pairs (Tunnels) on the IKE-interface."

        ::= { apSecurityIkeInterfaceInfoEntry 33 }

    apSecurityIkeInterfaceBlacklistAuthIDError OBJECT-TYPE
        SYNTAX		Unsigned32
        MAX-ACCESS	read-only
        STATUS		current
        DESCRIPTION
                "Number of Authentication ID Errors on the IKE-interface (blacklist)."
        ::= { apSecurityIkeInterfaceInfoEntry 34 }

    apSecurityIkeInterfaceRekeyOnSNoverflow OBJECT-TYPE 
        SYNTAX      Unsigned32
        MAX-ACCESS  read-only
        STATUS      current
        DESCRIPTION
                "Number of rekeys due to SN overflow on the IKE-interface."
        ::= { apSecurityIkeInterfaceInfoEntry 35 }
    
    apSecurityIkeInterfaceDPDFailSaDel OBJECT-TYPE
        SYNTAX      Unsigned32
        MAX-ACCESS  read-only
        STATUS      current
        DESCRIPTION
                "Number of SA's deleted due to DPD failure on the IKE-interface."
        ::= { apSecurityIkeInterfaceInfoEntry 36 }

    apSecurityIkeInterfaceEapOnlyAuthentication OBJECT-TYPE
        SYNTAX      Unsigned32
        MAX-ACCESS  read-only
        STATUS      current
        DESCRIPTION
                "Number of EAP_ONLY Auth requested by UEs on the IKE-interface."
        ::= { apSecurityIkeInterfaceInfoEntry 37 }

    apSecurityIkeInterfaceEapOnlyWithAuthPayload OBJECT-TYPE
        SYNTAX      Unsigned32
        MAX-ACCESS  read-only
        STATUS      current
        DESCRIPTION
                "Number of IKE_AUTH requests which contains both AUTH payload and EAP_ONLY notification on the IKE-interface."
        ::= { apSecurityIkeInterfaceInfoEntry 38 }
    
    apSecurityIkeInterfaceEapSimSucc OBJECT-TYPE
        SYNTAX      Counter32
        MAX-ACCESS  read-only
        STATUS      current
        DESCRIPTION
                "Number of successul authentications through eap-sim method on the IKE-interface."
        ::= { apSecurityIkeInterfaceInfoEntry 39 }
    
    apSecurityIkeInterfaceEapSimFail OBJECT-TYPE
        SYNTAX      Counter32 
        MAX-ACCESS  read-only
        STATUS      current
        DESCRIPTION
                "Number of  authentication failures through eap-sim method on the IKE-interface."
        ::= { apSecurityIkeInterfaceInfoEntry 40 }
    
    apSecurityIkeInterfaceEapAkaSucc OBJECT-TYPE
        SYNTAX      Counter32
        MAX-ACCESS  read-only
        STATUS      current
        DESCRIPTION
                "Number of successul authentications through eap-aka method on the IKE-interface."
        ::= { apSecurityIkeInterfaceInfoEntry 41 }
    
    apSecurityIkeInterfaceEapAkaFail OBJECT-TYPE
        SYNTAX      Counter32
        MAX-ACCESS  read-only
        STATUS      current
        DESCRIPTION
                "Number of  authentication failures through eap-sim method on the IKE-interface."
        ::= { apSecurityIkeInterfaceInfoEntry 42 }

    apSecurityIkeInterfaceEapAkaPrimeSucc OBJECT-TYPE
        SYNTAX      Counter32
        MAX-ACCESS  read-only
        STATUS      current
        DESCRIPTION
                "Number of successul authentications through eap-aka-prime method on the IKE-interface."
        ::= { apSecurityIkeInterfaceInfoEntry 43 }
    
    apSecurityIkeInterfaceEapAkaPrimeFail OBJECT-TYPE
        SYNTAX      Counter32
        MAX-ACCESS  read-only
        STATUS      current
        DESCRIPTION
                "Number of  authentication failures through eap-aka-prime method on the IKE-interface."
        ::= { apSecurityIkeInterfaceInfoEntry 44 }
    
    apSecurityIkeInterfaceEapTlsSucc OBJECT-TYPE
        SYNTAX      Counter32
        MAX-ACCESS  read-only
        STATUS      current
        DESCRIPTION
                "Number of successul authentications through eap-tls method on the IKE-interface."
        ::= { apSecurityIkeInterfaceInfoEntry 45 }
    
    apSecurityIkeInterfaceEapTlsFail OBJECT-TYPE
        SYNTAX      Counter32
        MAX-ACCESS  read-only
        STATUS      current
        DESCRIPTION
                "Number of  authentication failures through eap-tls method on the IKE-interface."
        ::= { apSecurityIkeInterfaceInfoEntry 46 }
    
    apSecurityIkeInterfaceEapTtlsSucc OBJECT-TYPE
        SYNTAX      Counter32
        MAX-ACCESS  read-only
        STATUS      current
        DESCRIPTION
                "Number of successul authentications through eap-ttls method on the IKE-interface."
        ::= { apSecurityIkeInterfaceInfoEntry 47 }
    
    apSecurityIkeInterfaceEapTtlsFail OBJECT-TYPE
        SYNTAX      Counter32
        MAX-ACCESS  read-only
        STATUS      current
        DESCRIPTION
                "Number of  authentication failures through eap-ttls method on the IKE-interface."
        ::= { apSecurityIkeInterfaceInfoEntry 48 }


    apSecurityIkeInterfaceEapOtherSucc OBJECT-TYPE
        SYNTAX      Counter32
        MAX-ACCESS  read-only
        STATUS      current
        DESCRIPTION
                "Number of successul authentications through other eap methods on the IKE-interface."
        ::= { apSecurityIkeInterfaceInfoEntry 49 }
    
    apSecurityIkeInterfaceEapOtherFail OBJECT-TYPE
        SYNTAX      Counter32
        MAX-ACCESS  read-only
        STATUS      current
        DESCRIPTION
                "Number of  authentication failures through other eap methods on the IKE-interface."
        ::= { apSecurityIkeInterfaceInfoEntry 50 }

    apSecurityIkeInterfaceNatKeepAliveMsgsRecv OBJECT-TYPE
        SYNTAX      Counter32
        MAX-ACCESS  read-only
        STATUS      current
        DESCRIPTION
                "Number of NAT Keep Alive messages received on the IKE-interface."
        ::= { apSecurityIkeInterfaceInfoEntry 51 }

    apSecurityIkeInterfaceBroadcastOrMulticastMsgcRecv OBJECT-TYPE
        SYNTAX      Counter32
        MAX-ACCESS  read-only
        STATUS      current
        DESCRIPTION
                "Number of Broadcast or Multicast  messages received on the IKE-interface."
        ::= { apSecurityIkeInterfaceInfoEntry 52 }

    apSecurityIkeInterfaceIkeSaAuthMsgsRecv OBJECT-TYPE
        SYNTAX      Counter32
        MAX-ACCESS  read-only
        STATUS      current
        DESCRIPTION
                "Number of IKE AUTH messages received on the IKE-interface."
        ::= { apSecurityIkeInterfaceInfoEntry 53 }

    apSecurityIkeInterfaceIkeSaAuthMsgsSent OBJECT-TYPE
        SYNTAX      Counter32
        MAX-ACCESS  read-only
        STATUS      current
        DESCRIPTION
                "Number of IKE AUTH messages sent on the IKE-interface."
        ::= { apSecurityIkeInterfaceInfoEntry 54 }

    apSecurityIkeInterfaceIkeSaChildMsgsRecv OBJECT-TYPE
        SYNTAX      Counter32
        MAX-ACCESS  read-only
        STATUS      current
        DESCRIPTION
                "Number of IKE CHILD messages received on the IKE-interface."
        ::= { apSecurityIkeInterfaceInfoEntry 55 }

    apSecurityIkeInterfaceIkeSaChildMsgsSent OBJECT-TYPE
        SYNTAX      Counter32
        MAX-ACCESS  read-only
        STATUS      current
        DESCRIPTION
                "Number of IKE CHILD messages sent on the IKE-interface."
        ::= { apSecurityIkeInterfaceInfoEntry 56 }

    apSecurityIkeInterfaceIkeSaInfoMsgsRecv OBJECT-TYPE
        SYNTAX      Counter32
        MAX-ACCESS  read-only
        STATUS      current
        DESCRIPTION
                "Number of IKE INFO messages received on the IKE-interface."
        ::= { apSecurityIkeInterfaceInfoEntry 57 }

    apSecurityIkeInterfaceIkeSaInfoMsgsSent OBJECT-TYPE
        SYNTAX      Counter32
        MAX-ACCESS  read-only
        STATUS      current
        DESCRIPTION
                "Number of IKE INFO  messages sent on the IKE-interface."
        ::= { apSecurityIkeInterfaceInfoEntry 58 }

    apSecurityIkeInterfaceInIkeSaRekeyRequest OBJECT-TYPE
        SYNTAX      Counter32
        MAX-ACCESS  read-only
        STATUS      current
        DESCRIPTION
                "Number of IKE SA Rekey requests received on the IKE-interface."
        ::= { apSecurityIkeInterfaceInfoEntry 59 }

    apSecurityIkeInterfaceInIkeSaRekeyRequestSuccess OBJECT-TYPE
        SYNTAX      Counter32
        MAX-ACCESS  read-only
        STATUS      current
        DESCRIPTION
                "Number of successful IKE SA Rekey requests received on the IKE-interface."
        ::= { apSecurityIkeInterfaceInfoEntry 60 }

    apSecurityIkeInterfaceInIkeSaRekeyRequestFailure OBJECT-TYPE
        SYNTAX      Counter32
        MAX-ACCESS  read-only
        STATUS      current
        DESCRIPTION
                "Number of failure IKE SA Rekey requests received on the IKE-interface."
        ::= { apSecurityIkeInterfaceInfoEntry 61 }

    apSecurityIkeInterfaceOutIkeSaRekeyRequest OBJECT-TYPE
        SYNTAX      Counter32
        MAX-ACCESS  read-only
        STATUS      current
        DESCRIPTION
                "Number of IKE SA Rekey requests sent on the IKE-interface."
        ::= { apSecurityIkeInterfaceInfoEntry 62 }

    apSecurityIkeInterfaceOutIkeSaRekeyRequestSuccess OBJECT-TYPE
        SYNTAX      Counter32
        MAX-ACCESS  read-only
        STATUS      current
        DESCRIPTION
                "Number of successful IKE SA Rekey requests sent on the IKE-interface."
        ::= { apSecurityIkeInterfaceInfoEntry 63 }

    apSecurityIkeInterfaceOutIkeSaRekeyRequestFailure OBJECT-TYPE
        SYNTAX      Counter32
        MAX-ACCESS  read-only
        STATUS      current
        DESCRIPTION
                "Number of failure IKE SA Rekey requests sent on the IKE-interface."
        ::= { apSecurityIkeInterfaceInfoEntry 64 }

    apSecurityIkeInterfaceInIkeSaDeleteRequest OBJECT-TYPE
        SYNTAX      Counter32
        MAX-ACCESS  read-only
        STATUS      current
        DESCRIPTION
                "Number of IKE SA Delete requests received on the IKE-interface."
        ::= { apSecurityIkeInterfaceInfoEntry 65 }

    apSecurityIkeInterfaceInIkeSaDeleteRequestSuccess OBJECT-TYPE
        SYNTAX      Counter32
        MAX-ACCESS  read-only
        STATUS      current
        DESCRIPTION
                "Number of successful IKE SA Delete requests received on the IKE-interface."
        ::= { apSecurityIkeInterfaceInfoEntry 66 }

    apSecurityIkeInterfaceInIkeSaDeleteRequestFailure OBJECT-TYPE
        SYNTAX      Counter32
        MAX-ACCESS  read-only
        STATUS      current
        DESCRIPTION
                "Number of failure IKE SA Delete requests received on the IKE-interface."
        ::= { apSecurityIkeInterfaceInfoEntry 67 }

    apSecurityIkeInterfaceOutIkeSaDeleteRequest OBJECT-TYPE
        SYNTAX      Counter32
        MAX-ACCESS  read-only
        STATUS      current
        DESCRIPTION
                "Number of IKE SA Delete requests sent on the IKE-interface."
        ::= { apSecurityIkeInterfaceInfoEntry 68 }

    apSecurityIkeInterfaceHalfOpenSecurityAssociations OBJECT-TYPE
        SYNTAX		Counter32
        MAX-ACCESS	read-only
        STATUS		current
        DESCRIPTION
                "Number of Half Open Security Associations on the IKE-interface."
        ::= { apSecurityIkeInterfaceInfoEntry 69 }

    apSecurityIkeInterfaceIkeTunnelAvgHoldTime OBJECT-TYPE
        SYNTAX		Unsigned32
        MAX-ACCESS	read-only
        STATUS		current
        DESCRIPTION
                "IKE Tunnel Average Hold Time on the IKE-interface from system reset or latest stats reset."
        ::= { apSecurityIkeInterfaceInfoEntry 70 }

    apSecurityIkeInterfaceIkeTunnelAvgSetupTime OBJECT-TYPE
        SYNTAX		Unsigned32
        MAX-ACCESS	read-only
        STATUS		current
        DESCRIPTION
                "IKE Tunnel Average Setup Time on the IKE-interface from system reset or latest stats reset."
        ::= { apSecurityIkeInterfaceInfoEntry 71 }

    apSecurityIkeInterfaceMobikeSupportRequest OBJECT-TYPE
        SYNTAX      Counter32
        MAX-ACCESS  read-only
        STATUS      current                                                       
        DESCRIPTION
                "Number of Mobike Support requests recevied on the IKE-interface."
        ::= { apSecurityIkeInterfaceInfoEntry 72 }
    
    apSecurityIkeInterfaceMobikeSupportResponse OBJECT-TYPE
        SYNTAX      Counter32
        MAX-ACCESS  read-only
        STATUS      current                                                       
        DESCRIPTION
                "Number of Mobike Support response send on the IKE-interface."
        ::= { apSecurityIkeInterfaceInfoEntry 73 }
    
    apSecurityIkeInterfaceMobikeUpdateSAAddrRcvd OBJECT-TYPE
        SYNTAX      Counter32
        MAX-ACCESS  read-only
        STATUS      current                                                       
        DESCRIPTION
                "Number of Mobike Update SA Requests received on the IKE-interface."
        ::= { apSecurityIkeInterfaceInfoEntry 74 }
    
    apSecurityIkeInterfaceMobikeUpdateSASuccess OBJECT-TYPE
        SYNTAX      Counter32
        MAX-ACCESS  read-only
        STATUS      current                                                       
        DESCRIPTION
                "Number of Mobike Update SA succesfully completed on the IKE-interface."
        ::= { apSecurityIkeInterfaceInfoEntry 75 }
    
    apSecurityIkeInterfaceMobikeUpdateSAAddrFamMismatch OBJECT-TYPE
        SYNTAX      Counter32
        MAX-ACCESS  read-only
        STATUS      current                                                       
        DESCRIPTION
                "Number of Mobike Update SA request with IP address family mismatch on the IKE-interface."
        ::= { apSecurityIkeInterfaceInfoEntry 76 }
    
    apSecurityIkeInterfaceMobikeUpdateSAFailUnexpUpdate OBJECT-TYPE
        SYNTAX      Counter32
        MAX-ACCESS  read-only
        STATUS      current                                                       
        DESCRIPTION
                "Number of Unexpected Mobike Update SA requests on the IKE-interface."
        ::= { apSecurityIkeInterfaceInfoEntry 77 }
    
    apSecurityIkeInterfaceMobikeUpdateSASameAddress OBJECT-TYPE
        SYNTAX      Counter32
        MAX-ACCESS  read-only
        STATUS      current                                                       
        DESCRIPTION
                "Number of Mobike Update SA requests with same address on the IKE-interface."
        ::= { apSecurityIkeInterfaceInfoEntry 78 }
    
    apSecurityIkeInterfaceMobikeUpdateSAFailInternal OBJECT-TYPE
        SYNTAX      Counter32
        MAX-ACCESS  read-only
        STATUS      current                                                       
        DESCRIPTION
                "Number of Mobike Update SA address fail internal on the IKE-interface."
        ::= { apSecurityIkeInterfaceInfoEntry 79 }
    
    apSecurityIkeInterfaceMobikeReturnRouteCheckRequests OBJECT-TYPE
        SYNTAX      Counter32
        MAX-ACCESS  read-only
        STATUS      current                                                       
        DESCRIPTION
                "Number of Mobike Return Routability Check Requests sent on the IKE-interface."
        ::= { apSecurityIkeInterfaceInfoEntry 80 }
    
    apSecurityIkeInterfaceMobikeFailToSendRouteCheck OBJECT-TYPE
        SYNTAX      Counter32
        MAX-ACCESS  read-only
        STATUS      current                                                       
        DESCRIPTION
                "Number of Mobike Return Routability Check Requests failed to sent on the IKE-interface."
        ::= { apSecurityIkeInterfaceInfoEntry 81 }
    
    apSecurityIkeInterfaceMobikeReturnRouteCheckSuccess OBJECT-TYPE
        SYNTAX      Counter32
        MAX-ACCESS  read-only
        STATUS      current                                                       
        DESCRIPTION
                "Number of Mobike Return Routability Check Success on the IKE-interface."
        ::= { apSecurityIkeInterfaceInfoEntry 82 }
    
    apSecurityIkeInterfaceMobikeReturnRouteCheckTimeout OBJECT-TYPE
        SYNTAX      Counter32
        MAX-ACCESS  read-only
        STATUS      current                                                       
        DESCRIPTION
                "Number of Mobike Return Routability Check Timeouts on the IKE-interface."
        ::= { apSecurityIkeInterfaceInfoEntry 83 }
    
    apSecurityIkeInterfaceMobikeRouteCheckFailSAdel OBJECT-TYPE
        SYNTAX      Counter32
        MAX-ACCESS  read-only
        STATUS      current                                                       
        DESCRIPTION
                "Number of IKE SAs deleted because of Return Routability Check failure on the IKE-interface."
        ::= { apSecurityIkeInterfaceInfoEntry 84 }
    
    apSecurityIkeInterfaceMobikeIntSaCommFailSaDel OBJECT-TYPE
        SYNTAX      Counter32
        MAX-ACCESS  read-only
        STATUS      current                                                       
        DESCRIPTION
                "Number of IKE SAs deleted because of Internal SA Communication failure on the IKE-interface."
        ::= { apSecurityIkeInterfaceInfoEntry 85 }
    
    apSecurityIkeInterfaceMobikeMisMatchCookie2Errors OBJECT-TYPE
        SYNTAX      Counter32
        MAX-ACCESS  read-only
        STATUS      current                                                       
        DESCRIPTION
                "Number of Mobike COOKIE2 mismatch errors in Return Routability Response on the IKE-interface."
        ::= { apSecurityIkeInterfaceInfoEntry 86 }

    apSecurityIkeInterfaceTunnelTearDownRate OBJECT-TYPE
        SYNTAX		Unsigned32
        MAX-ACCESS	read-only
        STATUS		current
        DESCRIPTION
                "Number of Tunnels tear down per second averaged over 5sec window on the IKE-interface."
        ::= { apSecurityIkeInterfaceInfoEntry 87 }




-- certificate table (read only)
    apSecurityCertificateTable OBJECT-TYPE
        SYNTAX  	SEQUENCE OF ApSecurityCertificateEntry
        MAX-ACCESS      not-accessible
        STATUS  	current
        DESCRIPTION
                "The table of locally installed certifcate."
        ::= { apSecurityMIBObjects 10 }

    apSecurityCertificateEntry OBJECT-TYPE
        SYNTAX  	ApSecurityCertificateEntry
        MAX-ACCESS      not-accessible
        STATUS  	current
        DESCRIPTION
                "The certificate entry."
        INDEX   { apSecurityCertificateConfigId, apSecurityCertificateIndex }
        ::= { apSecurityCertificateTable 1 }

    ApSecurityCertificateEntry ::=
        SEQUENCE {
		apSecurityCertificateConfigId 		Unsigned32,
		apSecurityCertificateIndex 		Unsigned32,
                apSecurityCertificateRecordName         DisplayString,
                apSecurityCertificateCertSubject	DisplayString,
		apSecurityCertificateCertStart   	DisplayString,
		apSecurityCertificateCertExpire   	DisplayString,
                apSecurityCertificateCertIssuer		DisplayString,
		apSecurityCertificateCertIsCA           TruthValue
		}


    apSecurityCertificateConfigId OBJECT-TYPE
        SYNTAX          Unsigned32
        MAX-ACCESS      not-accessible
        STATUS          current
        DESCRIPTION
            "The internal configuration ID of the certificate. "
        ::= { apSecurityCertificateEntry 1 }

    apSecurityCertificateIndex OBJECT-TYPE
        SYNTAX          Unsigned32
        MAX-ACCESS      not-accessible
        STATUS          current
        DESCRIPTION
            "The internal index of the certificate. 
	    Combined with configuration ID is the unique ID of a certificate "
        ::= { apSecurityCertificateEntry 2 }

    apSecurityCertificateRecordName OBJECT-TYPE
        SYNTAX          DisplayString (SIZE(0..255))
        MAX-ACCESS      read-only
        STATUS          current
        DESCRIPTION
            "The SBC's configuration record name for the certificate. "
        ::= { apSecurityCertificateEntry 3 }

    apSecurityCertificateCertSubject OBJECT-TYPE
        SYNTAX          DisplayString (SIZE(0..255))
        MAX-ACCESS      read-only
        STATUS          current
        DESCRIPTION
            "The certificate subject. "
        ::= { apSecurityCertificateEntry 4 }

    apSecurityCertificateCertStart OBJECT-TYPE
        SYNTAX          DisplayString (SIZE(0..255))
        MAX-ACCESS      read-only
        STATUS          current
        DESCRIPTION
            "The start time and date of the certificate. "
        ::= { apSecurityCertificateEntry 5 }

    apSecurityCertificateCertExpire OBJECT-TYPE
        SYNTAX          DisplayString (SIZE(0..255))
        MAX-ACCESS      read-only
        STATUS          current
        DESCRIPTION
            "The expiration time and date of the certificate. "
        ::= { apSecurityCertificateEntry 6 }

    apSecurityCertificateCertIssuer OBJECT-TYPE
        SYNTAX          DisplayString (SIZE(0..255))
        MAX-ACCESS      read-only
        STATUS          current
        DESCRIPTION
            "The issuer of the certificate."
        ::= { apSecurityCertificateEntry 7 }

    apSecurityCertificateCertIsCA OBJECT-TYPE
        SYNTAX          TruthValue
        MAX-ACCESS      read-only
        STATUS          current
        DESCRIPTION
            "Boolean value indicating if the certificate is a CA certificate."
        ::= { apSecurityCertificateEntry 8 }

-- DHCP Stats 
    apSecurityDhcpInterfaceStatsTable OBJECT-TYPE
        SYNTAX          SEQUENCE OF ApSecurityDhcpInterfaceStatsEntry
        MAX-ACCESS      not-accessible
        STATUS          current
        DESCRIPTION
                "The table of Dhcp stats per dhcp-interface for DHCP negotiations."
        ::= { apSecurityMIBObjects 11 }

    apSecurityDhcpInterfaceStatsEntry OBJECT-TYPE
        SYNTAX         ApSecurityDhcpInterfaceStatsEntry
        MAX-ACCESS      not-accessible
        STATUS          current
        DESCRIPTION     "DHCP negotiation statistics for an DHCP-interface."
        INDEX   { apSecurityDhcpInterfaceType, apSecurityDhcpInterfaceAddress }
        ::= { apSecurityDhcpInterfaceStatsTable 1 }

    ApSecurityDhcpInterfaceStatsEntry ::=
        SEQUENCE {
                apSecurityDhcpInterfaceType                     InetAddressType,
                apSecurityDhcpInterfaceAddress                  InetAddress,
                apSecurityDhcpInterfaceDisRcvd			Counter32,
                apSecurityDhcpInterfaceOfferSent                Counter32,
                apSecurityDhcpInterfaceReqRcvd			Counter32,
                apSecurityDhcpInterfaceAckSent                  Counter32,
                apSecurityDhcpInterfaceNAckSent                 Counter32,
                apSecurityDhcpInterfaceFailures                 Counter32,
                apSecurityDhcpInterfaceRelRcvd			Counter32,
                apSecurityDhcpInterfaceOfferTimeouts            Counter32,
                apSecurityDhcpInterfaceLeaseTimeouts            Counter32,
                apSecurityDhcpInterfaceCurrentSessions 		Gauge32,
                apSecurityDhcpInterfaceMaxSessions              Unsigned32,
                apSecurityDhcpInterfaceTotalSessions            Gauge32

        }

    apSecurityDhcpInterfaceType OBJECT-TYPE
        SYNTAX          InetAddressType
        MAX-ACCESS      read-only
        STATUS          current
        DESCRIPTION
                "IPAddress type of the DHCP-interface"
        ::= { apSecurityDhcpInterfaceStatsEntry 1 }

    apSecurityDhcpInterfaceAddress OBJECT-TYPE
        SYNTAX          InetAddress
        MAX-ACCESS      read-only
        STATUS          current
        DESCRIPTION
                "IPAddress of  the DHCP-interface"
        ::= { apSecurityDhcpInterfaceStatsEntry 2 }

    apSecurityDhcpInterfaceDisRcvd OBJECT-TYPE
        SYNTAX          Counter32
        MAX-ACCESS      read-only
        STATUS          current
        DESCRIPTION
                "Number of DHCP Discover Requests on the DHCP-interface."
        ::= { apSecurityDhcpInterfaceStatsEntry 3 }

    apSecurityDhcpInterfaceOfferSent OBJECT-TYPE
        SYNTAX          Counter32
        MAX-ACCESS      read-only
        STATUS          current
        DESCRIPTION
                "Number of DHCP Offer sent on the DHCP-interface."
        ::= { apSecurityDhcpInterfaceStatsEntry 4 }

    apSecurityDhcpInterfaceReqRcvd OBJECT-TYPE
        SYNTAX          Counter32
        MAX-ACCESS      read-only
        STATUS          current
        DESCRIPTION
                "Number of DHCP Requests on the DHCP-interface."
        ::= { apSecurityDhcpInterfaceStatsEntry 5 }

    apSecurityDhcpInterfaceAckSent OBJECT-TYPE
        SYNTAX          Counter32
        MAX-ACCESS      read-only
        STATUS          current
        DESCRIPTION
                "Number of DHCP Acknowledge sent on the DHCP-interface."
        ::= { apSecurityDhcpInterfaceStatsEntry 6 }

    apSecurityDhcpInterfaceNAckSent OBJECT-TYPE
        SYNTAX          Counter32
        MAX-ACCESS      read-only
        STATUS          current
        DESCRIPTION
                "Number of DHCP NAcknowledge sent on the DHCP-interface."
        ::= { apSecurityDhcpInterfaceStatsEntry 7 }

    apSecurityDhcpInterfaceFailures OBJECT-TYPE
        SYNTAX          Counter32
        MAX-ACCESS      read-only
        STATUS          current
        DESCRIPTION
                "Number of DHCP Failures on DHCP-interface."
        ::= { apSecurityDhcpInterfaceStatsEntry 8 }

    apSecurityDhcpInterfaceRelRcvd OBJECT-TYPE
        SYNTAX          Counter32
        MAX-ACCESS      read-only
        STATUS          current
        DESCRIPTION
                "Number of DHCP release requests received on the DHCP-interface."
        ::= { apSecurityDhcpInterfaceStatsEntry 9 }

    apSecurityDhcpInterfaceOfferTimeouts OBJECT-TYPE
        SYNTAX          Counter32
        MAX-ACCESS      read-only
        STATUS          current
        DESCRIPTION
                "Number of Dhcp Offer timeouts happened on the DHCP-interface."
        ::= { apSecurityDhcpInterfaceStatsEntry 10 }

    apSecurityDhcpInterfaceLeaseTimeouts OBJECT-TYPE
        SYNTAX          Counter32
        MAX-ACCESS      read-only
        STATUS          current
        DESCRIPTION
                "Number of Dhcp lease timeouts happened on the DHCP-interface."
        ::= { apSecurityDhcpInterfaceStatsEntry 11 }

    apSecurityDhcpInterfaceCurrentSessions OBJECT-TYPE
        SYNTAX          Gauge32
        MAX-ACCESS      read-only
        STATUS          current
        DESCRIPTION
                "Number of Dhcp sessions currently active on this DHCP-interface."
        ::= { apSecurityDhcpInterfaceStatsEntry 12 }

    apSecurityDhcpInterfaceMaxSessions OBJECT-TYPE
        SYNTAX          Unsigned32
        MAX-ACCESS      read-only
        STATUS          current
        DESCRIPTION
                "Max Number of Dhcp sessions on the DHCP-interface."
        ::= { apSecurityDhcpInterfaceStatsEntry 13 }

    apSecurityDhcpInterfaceTotalSessions OBJECT-TYPE
        SYNTAX         	Gauge32
        MAX-ACCESS      read-only
        STATUS          current
        DESCRIPTION
                "Total Number of Dhcp sessions on the DHCP-interface."
        ::= { apSecurityDhcpInterfaceStatsEntry 14 }

-- GTP Stats 
    apSecurityGtpStatsTable OBJECT-TYPE
        SYNTAX          SEQUENCE OF ApSecurityGtpStatsEntry
        MAX-ACCESS      not-accessible
        STATUS          current
        DESCRIPTION
                "The table of Gtp stats per Gtp-profile for Gtp negotiations."
        ::= { apSecurityMIBObjects 12 }

    apSecurityGtpStatsEntry OBJECT-TYPE
        SYNTAX         ApSecurityGtpStatsEntry
        MAX-ACCESS     not-accessible
        STATUS         current
        DESCRIPTION    "Gtp negotiation statistics for a GTP-Profile."
        INDEX   { apSecurityGtpProfile }
        ::= { apSecurityGtpStatsTable 1 }

    ApSecurityGtpStatsEntry ::=
        SEQUENCE {
                apSecurityGtpProfile				DisplayString,
                apSecurityGtpAddressType                        InetAddressType,
                apSecurityGtpAddress				InetAddress,
                apSecurityGtpHost				DisplayString,
                apSecurityGtpTunnelsCreated			Counter32,
                apSecurityGtpCPDPReqSent			Counter32,
                apSecurityGtpCPDPReqRcvd			Counter32,
                apSecurityGtpCPDPSuccRespSent			Counter32,
                apSecurityGtpCPDPSuccRespRcvd			Counter32,
                apSecurityGtpCPDPFailRespSent			Counter32,
                apSecurityGtpCPDPFailRespRcvd			Counter32,
                apSecurityGtpCPDPIncompleteRespRcvd		Counter32,
                apSecurityGtpCPDPRespCtxtNotFound		Counter32,
                apSecurityGtpCPDPFailInternalError		Counter32,
                apSecurityGtpCPDPRespTimeout           		Counter32,
                apSecurityGtpUPDPReqSent			Counter32,
                apSecurityGtpUPDPReqRcvd			Counter32,
                apSecurityGtpUPDPSuccRespSent			Counter32,
                apSecurityGtpUPDPSuccRespRcvd			Counter32,
                apSecurityGtpUPDPFailRespSent            	Counter32,
                apSecurityGtpUPDPFailRespRcvd			Counter32,
                apSecurityGtpUPDPRespTimeout			Counter32,
                apSecurityGtpDPDPReqSent			Counter32,
                apSecurityGtpDPDPReqRcvd			Counter32,
                apSecurityGtpDPDPSuccRespSent			Counter32,
                apSecurityGtpDPDPSuccRespRcvd			Counter32,
                apSecurityGtpDPDPFailRespSent			Counter32,
                apSecurityGtpDPDPFailRespRcvd           	Counter32,
                apSecurityGtpDPDPRespTimeout			Counter32,
                apSecurityGtpVersionNotSuppSent			Counter32,
                apSecurityGtpVersionNotSuppRcvd			Counter32,
                apSecurityGTPCEchoReqSent			Counter32,
                apSecurityGTPCEchoReqRcvd			Counter32,
                apSecurityGTPCEchoRespSent			Counter32,
                apSecurityGTPCEchoRespRcvd			Counter32,
                apSecurityGTPCEchoRespTimeout			Counter32,
                apSecurityGTPUEchoReqSent			Counter32,
                apSecurityGTPUEchoReqRcvd			Counter32,
                apSecurityGTPUEchoRespSent			Counter32,
                apSecurityGTPUEchoRespRcvd			Counter32,
                apSecurityGTPUEchoRespTimeout			Counter32,
		apSecurityGtpV2CreateSesssionReqSent		Counter32,    
                apSecurityGtpV2CreateSesssionReqSentFail	Counter32,
                apSecurityGtpV2CreateSessionRespRcvd		Counter32,    
                apSecurityGtpV2CreateSessionRespFailRcvd	Counter32,
                apSecurityGtpV2CreateSessionRespTimeout		Counter32, 
                apSecurityGtpV2DeleteSessionReqSent		Counter32,     
                apSecurityGtpV2DeleteSessionReqSentFail		Counter32, 
                apSecurityGtpV2DeleteSessionRespRcvd		Counter32,    
                apSecurityGtpV2DeleteSessionRespRcvdFail	Counter32,
                apSecurityGtpV2DeleteSessionRespTimeout		Counter32,
                apSecurityGtpV2DeleteBearerReqRcvd		Counter32,      
                apSecurityGtpV2DeleteBearerReqRcvdFail		Counter32,  
                apSecurityGtpV2DeleteBearerRespSent		Counter32,     
                apSecurityGtpV2DeleteBearerRespSentFail		Counter32, 
                apSecurityGtpV2CreateBearerReqRcvd		Counter32,      
                apSecurityGtpV2CreateBearerReqRcvdFail		Counter32,  
                apSecurityGtpV2CreateBearerRespSent		Counter32,     
                apSecurityGtpV2CreateBearerRespSentFail		Counter32, 
                apSecurityGtpV2UpdateBearerReqRcvd		Counter32,      
                apSecurityGtpV2UpdateBearerReqRcvdFail		Counter32,  
                apSecurityGtpV2UpdateBearerRespSent		Counter32,     
                apSecurityGtpV2UpdateBearerRespSentFail		Counter32, 
                apSecurityGTPErrorIndRcvd			Counter32,
                apSecurityGtpV2CreateSessRespPPMAddFail         Counter32,
                apSecurityGtpV2DeleteBReqRcvdPPMDelFail         Counter32,
                apSecurityGtpV2CreateBReqPPMAddFail		Counter32,
                apSecurityGtpV2UpdateBReqPPMUpdateFail		Counter32,
                apSecurityGtpV2StandbyDefBrerPPMAddFail		Counter32,
                apSecurityGtpV2StandbyDedBrerPPMAddFail		Counter32,
                apSecurityGtpV2StandbyDefBrerPPMDelFail		Counter32,
                apSecurityGtpV2StandbyDedBrerPPMDelFail		Counter32

        }

    apSecurityGtpProfile OBJECT-TYPE
        SYNTAX          DisplayString
        MAX-ACCESS      read-only
        STATUS          current
        DESCRIPTION
                "Name of the Gtp-Profile"
        ::= { apSecurityGtpStatsEntry 1 }

    apSecurityGtpAddressType OBJECT-TYPE
        SYNTAX          InetAddressType 
        MAX-ACCESS      read-only
        STATUS          current
        DESCRIPTION
                "IPAddressType of  the Gtp Profile"
        ::= { apSecurityGtpStatsEntry 2 }
    
    apSecurityGtpAddress OBJECT-TYPE
        SYNTAX          InetAddress
        MAX-ACCESS      read-only
        STATUS          current
        DESCRIPTION
                "IPAddress of the Gtp Server"
        ::= { apSecurityGtpStatsEntry 3 }
    
    apSecurityGtpHost OBJECT-TYPE
        SYNTAX          DisplayString
        MAX-ACCESS      read-only
        STATUS          current
        DESCRIPTION
                "Name of the Gtp Server"
        ::= { apSecurityGtpStatsEntry 4 }


    apSecurityGtpTunnelsCreated OBJECT-TYPE
        SYNTAX          Counter32
        MAX-ACCESS      read-only
        STATUS          current
        DESCRIPTION
                "Number of Gtp tunnels created on the Gtp Profile."
        ::= { apSecurityGtpStatsEntry 5 }

    apSecurityGtpCPDPReqSent OBJECT-TYPE
        SYNTAX          Counter32
        MAX-ACCESS      read-only
        STATUS          current
        DESCRIPTION
                "Number of CreatePDP request sent on the Gtp Profile."
        ::= { apSecurityGtpStatsEntry 6 }

    apSecurityGtpCPDPReqRcvd OBJECT-TYPE
        SYNTAX          Counter32
        MAX-ACCESS      read-only
        STATUS          current
        DESCRIPTION
                "Number of CreatePDP request received on the Gtp Profile."
        ::= { apSecurityGtpStatsEntry 7 }

    apSecurityGtpCPDPSuccRespSent OBJECT-TYPE
        SYNTAX          Counter32
        MAX-ACCESS      read-only
        STATUS          current
        DESCRIPTION
                "Number of CreatePDP success response sent on the Gtp Profile."
        ::= { apSecurityGtpStatsEntry 8 }

    apSecurityGtpCPDPSuccRespRcvd OBJECT-TYPE
        SYNTAX          Counter32
        MAX-ACCESS      read-only
        STATUS          current
        DESCRIPTION
                "Number of CreatePDP success response received on the Gtp Profile."
        ::= { apSecurityGtpStatsEntry 9 }

    apSecurityGtpCPDPFailRespSent OBJECT-TYPE
        SYNTAX          Counter32
        MAX-ACCESS      read-only
        STATUS          current
        DESCRIPTION
                "Number of CreatePDP failed response sent on the Gtp Profile."
        ::= { apSecurityGtpStatsEntry 10 }

    apSecurityGtpCPDPFailRespRcvd OBJECT-TYPE
        SYNTAX          Counter32
        MAX-ACCESS      read-only
        STATUS          current
        DESCRIPTION
                "Number of CreatePDP failed response received on the Gtp Profile."
        ::= { apSecurityGtpStatsEntry 11 }

    apSecurityGtpCPDPIncompleteRespRcvd OBJECT-TYPE
        SYNTAX          Counter32
        MAX-ACCESS      read-only
        STATUS          current
        DESCRIPTION
                "Number of CreatePDP incomplete response received on the Gtp Profile"
        ::= { apSecurityGtpStatsEntry 12 }

    apSecurityGtpCPDPRespCtxtNotFound OBJECT-TYPE
        SYNTAX          Counter32
        MAX-ACCESS      read-only
        STATUS          current
        DESCRIPTION
                "Number of CreatePDP response context not found  messages on the Gtp Profile."
        ::= { apSecurityGtpStatsEntry 13 }

    apSecurityGtpCPDPFailInternalError OBJECT-TYPE
        SYNTAX          Counter32
        MAX-ACCESS      read-only
        STATUS          current
        DESCRIPTION
                "Number of CreatePDP failed internal errors on the Gtp Profile."
        ::= { apSecurityGtpStatsEntry 14 }

    apSecurityGtpCPDPRespTimeout OBJECT-TYPE
        SYNTAX          Counter32
        MAX-ACCESS      read-only
        STATUS          current
        DESCRIPTION
                "Number of CreatePDP response timeout messages on the Gtp Profile."
        ::= { apSecurityGtpStatsEntry 15 }

    apSecurityGtpUPDPReqSent OBJECT-TYPE
        SYNTAX          Counter32
        MAX-ACCESS      read-only
        STATUS          current
        DESCRIPTION
                "Number of UpdatePDP request sent on the Gtp Profile."
        ::= { apSecurityGtpStatsEntry 16 }

    apSecurityGtpUPDPReqRcvd OBJECT-TYPE
        SYNTAX         	Counter32
        MAX-ACCESS      read-only
        STATUS          current
        DESCRIPTION
                "Number of UpdatePDP request received on the Gtp Profile."
        ::= { apSecurityGtpStatsEntry 17 }
    
   apSecurityGtpUPDPSuccRespSent OBJECT-TYPE
        SYNTAX         	Counter32
        MAX-ACCESS      read-only
        STATUS          current
        DESCRIPTION
                "Number of UpdatePDP success response sent on the Gtp Profile."
        ::= { apSecurityGtpStatsEntry 18 }
    
   apSecurityGtpUPDPSuccRespRcvd OBJECT-TYPE
        SYNTAX         	Counter32
        MAX-ACCESS      read-only
        STATUS          current
        DESCRIPTION
                "Number of UpdatePDP success response received on the Gtp Profile."
        ::= { apSecurityGtpStatsEntry 19 }
   
   apSecurityGtpUPDPFailRespSent OBJECT-TYPE
        SYNTAX         	Counter32
        MAX-ACCESS      read-only
        STATUS          current
        DESCRIPTION
                "Number of UpdatePDP failed response sent on the Gtp Profile."
        ::= { apSecurityGtpStatsEntry 20 }
   
    apSecurityGtpUPDPFailRespRcvd OBJECT-TYPE
        SYNTAX         	Counter32
        MAX-ACCESS      read-only
        STATUS          current
        DESCRIPTION
                "Number of UpdatePDP failed response received on the Gtp Profile."
        ::= { apSecurityGtpStatsEntry 21 }
    
    apSecurityGtpUPDPRespTimeout OBJECT-TYPE
        SYNTAX         	Counter32
        MAX-ACCESS      read-only
        STATUS          current
        DESCRIPTION
                "Number of UpdatePDP responses timed out on the Gtp Profile."
        ::= { apSecurityGtpStatsEntry 22 }
   
    apSecurityGtpDPDPReqSent OBJECT-TYPE
        SYNTAX         	Counter32
        MAX-ACCESS      read-only
        STATUS          current
        DESCRIPTION
                "Number of DeletePDP request sent on the gtp Profile."
        ::= { apSecurityGtpStatsEntry 23 }
   
    apSecurityGtpDPDPReqRcvd OBJECT-TYPE
        SYNTAX         	Counter32
        MAX-ACCESS      read-only
        STATUS          current
        DESCRIPTION
                "Number of DeletePDP request received on the Gtp Profile."
        ::= { apSecurityGtpStatsEntry 24 }
    
    apSecurityGtpDPDPSuccRespSent OBJECT-TYPE
        SYNTAX         	Counter32
        MAX-ACCESS      read-only
        STATUS          current
        DESCRIPTION
                "Number of DeletePDP success response sent on the Gtp Profile."
        ::= { apSecurityGtpStatsEntry 25 }
    
    apSecurityGtpDPDPSuccRespRcvd OBJECT-TYPE
        SYNTAX         	Counter32
        MAX-ACCESS      read-only
        STATUS          current
        DESCRIPTION
                "Number of DeletePDP success response received on the Gtp Profile."
        ::= { apSecurityGtpStatsEntry 26 }
    
    apSecurityGtpDPDPFailRespSent OBJECT-TYPE
        SYNTAX         	Counter32
        MAX-ACCESS      read-only
        STATUS          current
        DESCRIPTION
                "Number of DeletePDP failed response sent on the Gtp Profile."
        ::= { apSecurityGtpStatsEntry 27 }
    
    apSecurityGtpDPDPFailRespRcvd OBJECT-TYPE
        SYNTAX         	Counter32
        MAX-ACCESS      read-only
        STATUS          current
        DESCRIPTION
                "Number of DeletePDP failed response received on the Gtp Profile."
        ::= { apSecurityGtpStatsEntry 28 }
    
    apSecurityGtpDPDPRespTimeout OBJECT-TYPE
        SYNTAX         	Counter32
        MAX-ACCESS      read-only
        STATUS          current
        DESCRIPTION
                "Number of DeletePDP response timedout on the Gtp Profile."
        ::= { apSecurityGtpStatsEntry 29 }
    
    apSecurityGtpVersionNotSuppSent OBJECT-TYPE
        SYNTAX         	Counter32
        MAX-ACCESS      read-only
        STATUS          current
        DESCRIPTION
                "Number of Gtp version not supported messages sent on the Gtp Profile."
        ::= { apSecurityGtpStatsEntry 30 }
    
    apSecurityGtpVersionNotSuppRcvd OBJECT-TYPE
        SYNTAX         	Counter32
        MAX-ACCESS      read-only
        STATUS          current
        DESCRIPTION
                "Number of Gtp verson not supported messages received on the Gtp Profile."
        ::= { apSecurityGtpStatsEntry 31 }
    
     apSecurityGTPCEchoReqSent OBJECT-TYPE
        SYNTAX         	Counter32
        MAX-ACCESS      read-only
        STATUS          current
        DESCRIPTION
                "Number of Echo request sent on the control plane."
        ::= { apSecurityGtpStatsEntry 32 }
     
     apSecurityGTPCEchoReqRcvd OBJECT-TYPE
        SYNTAX         	Counter32
        MAX-ACCESS      read-only
        STATUS          current
        DESCRIPTION
                "Number of Echo request received on the control plane."
        ::= { apSecurityGtpStatsEntry 33 }
     
     apSecurityGTPCEchoRespSent OBJECT-TYPE
        SYNTAX         	Counter32
        MAX-ACCESS      read-only
        STATUS          current
        DESCRIPTION
                "Number of Echo response sent on the control plane."
        ::= { apSecurityGtpStatsEntry 34 }
     
     apSecurityGTPCEchoRespRcvd OBJECT-TYPE
        SYNTAX         	Counter32
        MAX-ACCESS      read-only
        STATUS          current
        DESCRIPTION
                "Number of Echo response received on the control plane."
        ::= { apSecurityGtpStatsEntry 35 }
     
     apSecurityGTPCEchoRespTimeout OBJECT-TYPE
        SYNTAX         	Counter32
        MAX-ACCESS      read-only
        STATUS          current
        DESCRIPTION
                "Number of Echo response timedout on the control plane."
        ::= { apSecurityGtpStatsEntry 36 }
     
     apSecurityGTPUEchoReqSent OBJECT-TYPE
        SYNTAX         	Counter32
        MAX-ACCESS      read-only
        STATUS          current
        DESCRIPTION
                "Number of Echo request sent on the user plane."
        ::= { apSecurityGtpStatsEntry 37 }
     
     apSecurityGTPUEchoReqRcvd OBJECT-TYPE
        SYNTAX         	Counter32
        MAX-ACCESS      read-only
        STATUS          current
        DESCRIPTION
                "Number of Echo request received on the user plane."
        ::= { apSecurityGtpStatsEntry 38 }
     
     apSecurityGTPUEchoRespSent OBJECT-TYPE
        SYNTAX         	Counter32
        MAX-ACCESS      read-only
        STATUS          current
        DESCRIPTION
                "Number of Echo response sent on the user plane."
        ::= { apSecurityGtpStatsEntry 39 }
     
     apSecurityGTPUEchoRespRcvd OBJECT-TYPE
        SYNTAX         	Counter32
        MAX-ACCESS      read-only
        STATUS          current
        DESCRIPTION
                "Number of Echo response received on the user plane."
        ::= { apSecurityGtpStatsEntry 40 }
     
     apSecurityGTPUEchoRespTimeout OBJECT-TYPE
        SYNTAX         	Counter32
        MAX-ACCESS      read-only
        STATUS          current
        DESCRIPTION
                "Number of Echo response timeout on the user plane."
        ::= { apSecurityGtpStatsEntry 41 }
     apSecurityGtpV2CreateSesssionReqSent OBJECT-TYPE
        SYNTAX         	Counter32
        MAX-ACCESS      read-only
        STATUS         	 current
        DESCRIPTION
                "Number of Create Session Requests sent on the control plane."
        ::= { apSecurityGtpStatsEntry 42 }

     apSecurityGtpV2CreateSesssionReqSentFail OBJECT-TYPE
        SYNTAX         	Counter32
        MAX-ACCESS      read-only
        STATUS         	 current
        DESCRIPTION
                "Number of Create Session Requests send failed on the control plane."
        ::= { apSecurityGtpStatsEntry 43 }

     apSecurityGtpV2CreateSessionRespRcvd OBJECT-TYPE
        SYNTAX         	Counter32
        MAX-ACCESS      read-only
        STATUS         	 current
        DESCRIPTION
                "Number of Create Session Response Received on the control plane."
        ::= { apSecurityGtpStatsEntry 44 }

     apSecurityGtpV2CreateSessionRespFailRcvd OBJECT-TYPE
        SYNTAX         	Counter32
        MAX-ACCESS      read-only
        STATUS         	 current
        DESCRIPTION
                "Number of Failed Create Session Response Received on the control plane."
        ::= { apSecurityGtpStatsEntry 45 }

     apSecurityGtpV2CreateSessionRespTimeout OBJECT-TYPE
        SYNTAX         	Counter32
        MAX-ACCESS      read-only
        STATUS         	 current
        DESCRIPTION
                "Number of Create Session Response timeout on the control plane."
        ::= { apSecurityGtpStatsEntry 46 }

     apSecurityGtpV2DeleteSessionReqSent OBJECT-TYPE
        SYNTAX         	Counter32
        MAX-ACCESS      read-only
        STATUS         	 current
        DESCRIPTION
                "Number of Delete Session Request sent on the control plane."
        ::= { apSecurityGtpStatsEntry 47 }

     apSecurityGtpV2DeleteSessionReqSentFail OBJECT-TYPE
        SYNTAX         	Counter32
        MAX-ACCESS      read-only
        STATUS         	 current
        DESCRIPTION
                "Number of Delete Session Request sent Failed on the control plane."
        ::= { apSecurityGtpStatsEntry 48 }

     apSecurityGtpV2DeleteSessionRespRcvd OBJECT-TYPE
        SYNTAX         	Counter32
        MAX-ACCESS      read-only
        STATUS         	 current
        DESCRIPTION
                "Number of Delete Session Response Received on the control plane."
        ::= { apSecurityGtpStatsEntry 49 }

     apSecurityGtpV2DeleteSessionRespRcvdFail OBJECT-TYPE
        SYNTAX         	Counter32
        MAX-ACCESS      read-only
        STATUS         	 current
        DESCRIPTION
                "Number of Failed Delete Session Response Received on the control plane."
        ::= { apSecurityGtpStatsEntry 50 }

     apSecurityGtpV2DeleteSessionRespTimeout OBJECT-TYPE
        SYNTAX         	Counter32
        MAX-ACCESS      read-only
        STATUS         	 current
        DESCRIPTION
                "Number of Delete Session Response Timeout on the control plane."
        ::= { apSecurityGtpStatsEntry 51 }

     apSecurityGtpV2DeleteBearerReqRcvd OBJECT-TYPE
        SYNTAX         	Counter32
        MAX-ACCESS      read-only
        STATUS         	 current
        DESCRIPTION
                "Number of Delete Bearer Requests Received on the control plane."
        ::= { apSecurityGtpStatsEntry 52 }

     apSecurityGtpV2DeleteBearerReqRcvdFail OBJECT-TYPE
        SYNTAX         	Counter32
        MAX-ACCESS      read-only
        STATUS         	 current
        DESCRIPTION
                "Number of Failed Delete Bearer Requests Received on the control plane."
        ::= { apSecurityGtpStatsEntry 53 }

     apSecurityGtpV2DeleteBearerRespSent OBJECT-TYPE
        SYNTAX         	Counter32
        MAX-ACCESS      read-only
        STATUS         	 current
        DESCRIPTION
                "Number of Delete Bearer Responses sent on the control plane."
        ::= { apSecurityGtpStatsEntry 54 }

     apSecurityGtpV2DeleteBearerRespSentFail OBJECT-TYPE
        SYNTAX         	Counter32
        MAX-ACCESS      read-only
        STATUS         	 current
        DESCRIPTION
                "Number of Failed Delete Bearer Responses sent on the control plane."
        ::= { apSecurityGtpStatsEntry 55 }

     apSecurityGtpV2CreateBearerReqRcvd OBJECT-TYPE
        SYNTAX         	Counter32
        MAX-ACCESS      read-only
        STATUS         	 current
        DESCRIPTION
                "Number of Create Bearer Requests Received on the control plane."
        ::= { apSecurityGtpStatsEntry 56 }

     apSecurityGtpV2CreateBearerReqRcvdFail OBJECT-TYPE
        SYNTAX         	Counter32
        MAX-ACCESS      read-only
        STATUS         	 current
        DESCRIPTION
                "Number of Failed Create Bearer Requests Received on the control plane."
        ::= { apSecurityGtpStatsEntry 57 }

     apSecurityGtpV2CreateBearerRespSent OBJECT-TYPE
        SYNTAX         	Counter32
        MAX-ACCESS      read-only
        STATUS         	 current
        DESCRIPTION
                "Number of Create Bearer Responses sent on the control plane."
        ::= { apSecurityGtpStatsEntry 58 }

     apSecurityGtpV2CreateBearerRespSentFail OBJECT-TYPE
        SYNTAX         	Counter32
        MAX-ACCESS      read-only
        STATUS         	 current
        DESCRIPTION
                "Number of Failed Create Bearer Responses sent on the control plane."
        ::= { apSecurityGtpStatsEntry 59 }

     apSecurityGtpV2UpdateBearerReqRcvd OBJECT-TYPE
        SYNTAX         	Counter32
        MAX-ACCESS      read-only
        STATUS         	 current
        DESCRIPTION
                "Number of Update Bearer Requests Received on the control plane."
        ::= { apSecurityGtpStatsEntry 60 }

     apSecurityGtpV2UpdateBearerReqRcvdFail OBJECT-TYPE
        SYNTAX         	Counter32
        MAX-ACCESS      read-only
        STATUS         	 current
        DESCRIPTION
                "Number of Failed Update Bearer Requests Received on the control plane."
        ::= { apSecurityGtpStatsEntry 61 }

     apSecurityGtpV2UpdateBearerRespSent OBJECT-TYPE
        SYNTAX         	Counter32
        MAX-ACCESS      read-only
        STATUS         	 current
        DESCRIPTION
                "Number of Update Bearer Responses sent on the control plane."
        ::= { apSecurityGtpStatsEntry 62 }

     apSecurityGtpV2UpdateBearerRespSentFail OBJECT-TYPE
        SYNTAX         	Counter32
        MAX-ACCESS      read-only
        STATUS         	 current
        DESCRIPTION
                "Number of Failed Update Bearer Responses sent on the control plane."
        ::= { apSecurityGtpStatsEntry 63 }

     apSecurityGTPErrorIndRcvd	OBJECT-TYPE
        SYNTAX          Counter32
        MAX-ACCESS      read-only
        STATUS           current
        DESCRIPTION
                "Number of Error Indication Messages received on the control plane."
        ::= { apSecurityGtpStatsEntry 64 }

     apSecurityGtpV2CreateSessRespPPMAddFail	OBJECT-TYPE
        SYNTAX          Counter32
        MAX-ACCESS      read-only
        STATUS           current
        DESCRIPTION
                "Number of PPM Add failure for Create Session Responses received."
        ::= { apSecurityGtpStatsEntry 65 }

     apSecurityGtpV2DeleteBReqRcvdPPMDelFail	OBJECT-TYPE
        SYNTAX          Counter32
        MAX-ACCESS      read-only
        STATUS           current
        DESCRIPTION
                "Number of PPM Add failure for Delete Bearer Requests received."
        ::= { apSecurityGtpStatsEntry 66 }

     apSecurityGtpV2CreateBReqPPMAddFail	OBJECT-TYPE
        SYNTAX          Counter32
        MAX-ACCESS      read-only
        STATUS           current
        DESCRIPTION
                "Number of PPM Add failure for Create Bearer Requests received."
        ::= { apSecurityGtpStatsEntry 67 }

     apSecurityGtpV2UpdateBReqPPMUpdateFail	OBJECT-TYPE
        SYNTAX          Counter32
        MAX-ACCESS      read-only
        STATUS           current
        DESCRIPTION
                "Number of PPM Add failure for Update Bearer Requests received."
        ::= { apSecurityGtpStatsEntry 68 }

     apSecurityGtpV2StandbyDefBrerPPMAddFail	OBJECT-TYPE
        SYNTAX          Counter32
        MAX-ACCESS      read-only
        STATUS           current
        DESCRIPTION
                "Number of Default Bearer Add failure in Standby."
        ::= { apSecurityGtpStatsEntry 69 }

     apSecurityGtpV2StandbyDedBrerPPMAddFail	OBJECT-TYPE
        SYNTAX          Counter32
        MAX-ACCESS      read-only
        STATUS           current
        DESCRIPTION
                "Number of Dedicated Bearer Add failure in Standby."
        ::= { apSecurityGtpStatsEntry 70 }

     apSecurityGtpV2StandbyDefBrerPPMDelFail	OBJECT-TYPE
        SYNTAX          Counter32
        MAX-ACCESS      read-only
        STATUS           current
        DESCRIPTION
                "Number of Default Bearer Delete failure in Standby."
        ::= { apSecurityGtpStatsEntry 71 }

     apSecurityGtpV2StandbyDedBrerPPMDelFail	OBJECT-TYPE
        SYNTAX          Counter32
        MAX-ACCESS      read-only
        STATUS           current
        DESCRIPTION
                "Number of Dedicated Bearer Delete failure in Standby."
        ::= { apSecurityGtpStatsEntry 72 }

-- GTP Error Stats 
    apSecurityGtpErrorStatsTable OBJECT-TYPE
        SYNTAX          SEQUENCE OF ApSecurityGtpErrorStatsEntry
        MAX-ACCESS      not-accessible
        STATUS          current
        DESCRIPTION
                "The table of Gtp error stats per Gtp-profile for Gtp negotiations."
        ::= { apSecurityMIBObjects 13 }

    apSecurityGtpErrorStatsEntry OBJECT-TYPE
        SYNTAX         ApSecurityGtpErrorStatsEntry
        MAX-ACCESS     not-accessible
        STATUS         current
        DESCRIPTION    "Gtp negotiation error statistics for  GTP-Profile."
        AUGMENTS	{ apSecurityGtpStatsEntry }
        ::= { apSecurityGtpErrorStatsTable 1 }

    ApSecurityGtpErrorStatsEntry ::=
        SEQUENCE {
                apSecurityGtpMsgDiffVer				Counter32,
                apSecurityGtpInvalidMsgLen			Counter32,
                apSecurityGtpUnknownMsg				Counter32,
                apSecurityGtpUnexpectedMsg			Counter32,
                apSecurityGtpMissingMandIE			Counter32,
                apSecurityGtpMissingReqIE			Counter32,
                apSecurityGtpMissingContIE			Counter32,
                apSecurityGtpInvalidIELen			Counter32,
                apSecurityGtpInvalidMandIE			Counter32,
                apSecurityGtpInvalidOptIE			Counter32,
                apSecurityGtpUnknownIE				Counter32,
                apSecurityGtpInvalidSeqIE			Counter32,
                apSecurityGtpUnexpectedIE			Counter32,
                apSecurityGtpRepeatedIE				Counter32,
                apSecurityGtpIncorrectOptIE		   	Counter32,
                apSecurityGtpTunnelNonExistent			Counter32,
                apSecurityGtpInvalidMsgFormat			Counter32,
                apSecurityGtpErrorIndCtxtNotFound		Counter32,
		        apSecurityGtpInvalidPCOFormat			Counter32,
                apSecurityGtpSemanticTFTError			Counter32,
                apSecurityGtpSyntacticTFTError			Counter32,
                apSecurityGtpSemanticPFError			Counter32,
                apSecurityGtpSyntacticPFError			Counter32,
		        apSecurityGtpInvalidAPCOFormat			Counter32
        }
    
    apSecurityGtpMsgDiffVer OBJECT-TYPE
        SYNTAX          Counter32
        MAX-ACCESS      read-only
        STATUS          current
        DESCRIPTION
                "The count of  messages with different Gtp version on Gtp profile."
        ::= { apSecurityGtpErrorStatsEntry 1 }
    
    apSecurityGtpInvalidMsgLen OBJECT-TYPE
        SYNTAX          Counter32
        MAX-ACCESS      read-only
        STATUS          current
        DESCRIPTION
                "The count of Gtp messages with invalid length on Gtp profile."
        ::= { apSecurityGtpErrorStatsEntry 2 }

    apSecurityGtpUnknownMsg OBJECT-TYPE
        SYNTAX          Counter32
        MAX-ACCESS      read-only
        STATUS          current
        DESCRIPTION
                "The count of unknown Gtp messages on Gtp profile."
        ::= { apSecurityGtpErrorStatsEntry 3 }
    
    apSecurityGtpUnexpectedMsg OBJECT-TYPE
        SYNTAX          Counter32
        MAX-ACCESS      read-only
        STATUS          current
        DESCRIPTION
                "The count of unexpected Gtp messages on Gtp profile."
        ::= { apSecurityGtpErrorStatsEntry 4 }

    
    apSecurityGtpMissingMandIE OBJECT-TYPE
        SYNTAX          Counter32
        MAX-ACCESS      read-only
        STATUS          current
        DESCRIPTION
                "The count of Gtp messages missing mandatory IE on Gtp profile"
        ::= { apSecurityGtpErrorStatsEntry 5 }


    apSecurityGtpMissingReqIE OBJECT-TYPE
        SYNTAX          Counter32
        MAX-ACCESS      read-only
        STATUS          current
        DESCRIPTION
                "The count of Gtp messages missing required IE on Gtp profile."
        ::= { apSecurityGtpErrorStatsEntry 6 }
    
    apSecurityGtpMissingContIE OBJECT-TYPE
        SYNTAX          Counter32
        MAX-ACCESS      read-only
        STATUS          current
        DESCRIPTION
                "The count of Gtp messages missing conditional IE on Gtp profile."
        ::= { apSecurityGtpErrorStatsEntry 7 }

    apSecurityGtpInvalidIELen OBJECT-TYPE
        SYNTAX          Counter32
        MAX-ACCESS      read-only
        STATUS          current
        DESCRIPTION
                "The count of Gtp messages with Invalid IE length on Gtp profile."
        ::= { apSecurityGtpErrorStatsEntry 8 }

    apSecurityGtpInvalidMandIE OBJECT-TYPE
        SYNTAX          Counter32
        MAX-ACCESS      read-only
        STATUS          current
        DESCRIPTION
                "The count of Gtp messages with invalid mandatory IE on Gtp profile."
        ::= { apSecurityGtpErrorStatsEntry 9 }

    apSecurityGtpInvalidOptIE OBJECT-TYPE
        SYNTAX          Counter32
        MAX-ACCESS      read-only
        STATUS          current
        DESCRIPTION
                "The count of Gtp messages with invalid optional IE on Gtp profile."
        ::= { apSecurityGtpErrorStatsEntry 10 }

    apSecurityGtpUnknownIE OBJECT-TYPE
        SYNTAX          Counter32
        MAX-ACCESS      read-only
        STATUS          current
        DESCRIPTION
                "The count of Gtp messages with unknown IE on Gtp profile."
        ::= { apSecurityGtpErrorStatsEntry 11 }

    apSecurityGtpInvalidSeqIE OBJECT-TYPE
        SYNTAX          Counter32
        MAX-ACCESS      read-only
        STATUS          current
        DESCRIPTION
                "The count of Gtp messages with invalid IE sequence on Gtp profile."
        ::= { apSecurityGtpErrorStatsEntry 12 }


    apSecurityGtpUnexpectedIE OBJECT-TYPE
        SYNTAX          Counter32
        MAX-ACCESS      read-only
        STATUS          current
        DESCRIPTION
                "The count of Gtp messages with unexpected IE on Gtp profile."
        ::= { apSecurityGtpErrorStatsEntry 13 }

    apSecurityGtpRepeatedIE OBJECT-TYPE
        SYNTAX          Counter32
        MAX-ACCESS      read-only
        STATUS          current
        DESCRIPTION
                "The count of Gtp messages with repeated IE on Gtp profile."
        ::= { apSecurityGtpErrorStatsEntry 14 }

    apSecurityGtpIncorrectOptIE OBJECT-TYPE
        SYNTAX          Counter32
        MAX-ACCESS      read-only
        STATUS          current
        DESCRIPTION
                "The count of Gtp messages with incorrect optional IE on Gtp profile."
        ::= { apSecurityGtpErrorStatsEntry 15 }


    apSecurityGtpTunnelNonExistent OBJECT-TYPE
        SYNTAX          Counter32
        MAX-ACCESS      read-only
        STATUS          current
        DESCRIPTION
                "The count of non existent Gtp tunnels on Gtp profile."
        ::= { apSecurityGtpErrorStatsEntry 16 }

    apSecurityGtpInvalidMsgFormat OBJECT-TYPE
        SYNTAX          Counter32
        MAX-ACCESS      read-only
        STATUS          current
        DESCRIPTION
                "The count of Gtp messages with invalid format on Gtp profile."
        ::= { apSecurityGtpErrorStatsEntry 17 }

    apSecurityGtpErrorIndCtxtNotFound OBJECT-TYPE
        SYNTAX          Counter32
        MAX-ACCESS      read-only
        STATUS          current
        DESCRIPTION
                "The count of missing error indication context on Gtp profile."
        ::= { apSecurityGtpErrorStatsEntry 18 }

    apSecurityGtpInvalidPCOFormat OBJECT-TYPE
        SYNTAX          Counter32
        MAX-ACCESS      read-only
        STATUS          current
        DESCRIPTION
                "The count of Gtp Messages with invalid PCO format on Gtp profile."
        ::= { apSecurityGtpErrorStatsEntry 19 }

    apSecurityGtpSemanticTFTError OBJECT-TYPE
        SYNTAX          Counter32
        MAX-ACCESS      read-only
        STATUS          current
        DESCRIPTION
                "The count of Semantic TFT Errors in Gtp Messages received."
        ::= { apSecurityGtpErrorStatsEntry 20 }

    apSecurityGtpSyntacticTFTError OBJECT-TYPE
        SYNTAX          Counter32
        MAX-ACCESS      read-only
        STATUS          current
        DESCRIPTION
                "The count of Syntactic TFT Errors in Gtp Messages received."
        ::= { apSecurityGtpErrorStatsEntry 21 }

    apSecurityGtpSemanticPFError OBJECT-TYPE
        SYNTAX          Counter32
        MAX-ACCESS      read-only
        STATUS          current
        DESCRIPTION
                "The count of Semantic PF Errors in Gtp Messages received."
        ::= { apSecurityGtpErrorStatsEntry 22 }

    apSecurityGtpSyntacticPFError OBJECT-TYPE
        SYNTAX          Counter32
        MAX-ACCESS      read-only
        STATUS          current
        DESCRIPTION
                "The count of Syntactic PF Errors in Gtp Messages received."
        ::= { apSecurityGtpErrorStatsEntry 23 }

    apSecurityGtpInvalidAPCOFormat OBJECT-TYPE
        SYNTAX          Counter32
        MAX-ACCESS      read-only
        STATUS          current
        DESCRIPTION
                "The count of Gtp Messages with invalid APCO format on Gtp profile."
        ::= { apSecurityGtpErrorStatsEntry 24 }

    -- SA IKE stats
    apSecuritySAIKEStats OBJECT IDENTIFIER ::= { apSecuritySAMIBObjects 1 }
 
    apSecSAIKEAddReqRcvd OBJECT-TYPE
        SYNTAX          Counter32
        MAX-ACCESS      read-only
        STATUS          current
        DESCRIPTION
           "Total number of IKE SA Add requests received"
        ::= { apSecuritySAIKEStats  1 }

    apSecSAIKEAddSuccessRespSent OBJECT-TYPE
        SYNTAX          Counter32
        MAX-ACCESS      read-only
        STATUS          current
        DESCRIPTION
           "Total number of success responses sent for IKE SA Add requests"
        ::= { apSecuritySAIKEStats  2 }

    apSecSAIKEAddFailRespSent OBJECT-TYPE
        SYNTAX          Counter32
        MAX-ACCESS      read-only
        STATUS          current
        DESCRIPTION
           "Total IKE ADD-SA fail responses sent"
        ::= { apSecuritySAIKEStats  3 }

    apSecSAIKEDelReqRcvd OBJECT-TYPE
        SYNTAX          Counter32
        MAX-ACCESS      read-only
        STATUS          current
        DESCRIPTION
           "Total IKE DEL-SA requests received"
        ::= { apSecuritySAIKEStats  4 }

    apSecSAIKEDelSuccessRespSent OBJECT-TYPE
        SYNTAX          Counter32
        MAX-ACCESS      read-only
        STATUS          current
        DESCRIPTION
           "Total IKE DEL-SA success responses sent"
        ::= { apSecuritySAIKEStats  5 }

    apSecSAIKEDelFailRespSent OBJECT-TYPE
        SYNTAX          Counter32
        MAX-ACCESS      read-only
        STATUS          current
        DESCRIPTION
           "Total IKE DEL-SA fail responses sent"
        ::= { apSecuritySAIKEStats  6 }

    apSecSAIKEAcquireReqSent OBJECT-TYPE
        SYNTAX          Counter32
        MAX-ACCESS      read-only
        STATUS          current
        DESCRIPTION
           "Total IKE ACQUIRE-SA requests sent"
        ::= { apSecuritySAIKEStats  7 }

    apSecSAIKEAcquireSuccessRespRcvd OBJECT-TYPE
        SYNTAX          Counter32
        MAX-ACCESS      read-only
        STATUS          current
        DESCRIPTION
           "Total IKE ACQUIRE-SA success responses received"
        ::= { apSecuritySAIKEStats  8 }

    apSecSAIKEAcquireFailRespRcvd OBJECT-TYPE
        SYNTAX          Counter32
        MAX-ACCESS      read-only
        STATUS          current
        DESCRIPTION
           "Total IKE ACQUIRE-SA fail responses received"
        ::= { apSecuritySAIKEStats  9 }

    apSecSAIKEAcquireTransactionTimeout OBJECT-TYPE
        SYNTAX          Counter32
        MAX-ACCESS      read-only
        STATUS          current
        DESCRIPTION
           "Total IKE ACQUIRE-SA transaction timeouts"
        ::= { apSecuritySAIKEStats  10 }

    apSecSAIKESaCreated OBJECT-TYPE
        SYNTAX          Counter32
        MAX-ACCESS      read-only
        STATUS          current
        DESCRIPTION
           "Total number of IKE SA added"
        ::= { apSecuritySAIKEStats  11 }

    apSecSAIKESaCreateFailed OBJECT-TYPE
        SYNTAX          Counter32
        MAX-ACCESS      read-only
        STATUS          current
        DESCRIPTION
           "Total number of IKE SA add failed"
        ::= { apSecuritySAIKEStats  12 }

    apSecSAIKESaDeleted OBJECT-TYPE
        SYNTAX          Counter32
        MAX-ACCESS      read-only
        STATUS          current
        DESCRIPTION
           "Total number of IKE SA deleted"
        ::= { apSecuritySAIKEStats  13 }

    apSecSAIKESaDeleteFailed OBJECT-TYPE
        SYNTAX          Counter32
        MAX-ACCESS      read-only
        STATUS          current
        DESCRIPTION
           "Total number of IKE SA delete failed"
        ::= { apSecuritySAIKEStats  14 }

    -- SA IMS_AKA STATS
    apSecuritySAIMSAKAStats OBJECT IDENTIFIER ::= { apSecuritySAMIBObjects 2 }

    apSecSAIMSAKAAddReqSent OBJECT-TYPE
        SYNTAX          Counter32
        MAX-ACCESS      read-only
        STATUS          current
        DESCRIPTION
           "Total number of IMS-AKA SA ADD requests sent"
        ::= { apSecuritySAIMSAKAStats  1 }

    apSecSAIMSAKAAddReqRcvd OBJECT-TYPE
        SYNTAX          Counter32
        MAX-ACCESS      read-only
        STATUS          current
        DESCRIPTION
           "Total number of IMS-AKA SA ADD requests received"
        ::= { apSecuritySAIMSAKAStats  2 }

    apSecSAIMSAKAAddSuccessRespSent OBJECT-TYPE
        SYNTAX          Counter32
        MAX-ACCESS      read-only
        STATUS          current
        DESCRIPTION
           "Total IMS-AKA ADD-SA success responses sent"
        ::= { apSecuritySAIMSAKAStats  3 }

    apSecSAIMSAKAAddSuccessRespRcvd OBJECT-TYPE
        SYNTAX          Counter32
        MAX-ACCESS      read-only
        STATUS          current
        DESCRIPTION
           "Total IMS-AKA ADD-SA success responses received"
        ::= { apSecuritySAIMSAKAStats  4 }

    apSecSAIMSAKAAddFailRespSent OBJECT-TYPE
        SYNTAX          Counter32
        MAX-ACCESS      read-only
        STATUS          current
        DESCRIPTION
           "Total IMS-AKA ADD-SA fail responses sent"
        ::= { apSecuritySAIMSAKAStats  5 }

    apSecSAIMSAKAAddFailInvalidParamRespSent OBJECT-TYPE
        SYNTAX          Counter32
        MAX-ACCESS      read-only
        STATUS          current
        DESCRIPTION
           "Total IMS-AKA ADD-SA fail messages sent due to invalid parameter"
        ::= { apSecuritySAIMSAKAStats  6 }

    apSecSAIMSAKAAddFailRespRcvd OBJECT-TYPE
        SYNTAX          Counter32
        MAX-ACCESS      read-only
        STATUS          current
        DESCRIPTION
           "Total IMS-AKA ADD-SA fail responses received"
        ::= { apSecuritySAIMSAKAStats  7 }

    apSecSAIMSAKAAddFailAddrMaskMismatch OBJECT-TYPE
        SYNTAX          Counter32
        MAX-ACCESS      read-only
        STATUS          current
        DESCRIPTION
           "Total IMS-AKA ADD-SA fail messages sent due to address mask mismatch"
        ::= { apSecuritySAIMSAKAStats  8 }

    apSecSAIMSAKAAddFailProtoParamsInvalid OBJECT-TYPE
        SYNTAX          Counter32
        MAX-ACCESS      read-only
        STATUS          current
        DESCRIPTION
           "Total IMS-AKA ADD-SA fail messages sent due to invalid protocol parameters"
        ::= { apSecuritySAIMSAKAStats  9 }

    apSecSAIMSAKAAddFailProtoDataInvalid OBJECT-TYPE
        SYNTAX          Counter32
        MAX-ACCESS      read-only
        STATUS          current
        DESCRIPTION
           "Total IMS-AKA ADD-SA fail messages sent due to invalid protocol data"
        ::= { apSecuritySAIMSAKAStats  10 }

    apSecSAIMSAKAAddTransactionTimeout OBJECT-TYPE
        SYNTAX          Counter32
        MAX-ACCESS      read-only
        STATUS          current
        DESCRIPTION
           "Total IMS-AKA ADD-SA transaction timeouts"
        ::= { apSecuritySAIMSAKAStats  11 }

    apSecSAIMSAKADelReqSent OBJECT-TYPE
        SYNTAX          Counter32
        MAX-ACCESS      read-only
        STATUS          current
        DESCRIPTION
           "Total IMS-AKA DEL-SA requests sent"
        ::= { apSecuritySAIMSAKAStats  12 }

    apSecSAIMSAKADelReqRcvd OBJECT-TYPE
        SYNTAX          Counter32
        MAX-ACCESS      read-only
        STATUS          current
        DESCRIPTION
           "Total IMS-AKA DEL-SA requests received"
        ::= { apSecuritySAIMSAKAStats  13 }

    apSecSAIMSAKADelSuccessRespSent OBJECT-TYPE
        SYNTAX          Counter32
        MAX-ACCESS      read-only
        STATUS          current
        DESCRIPTION
           "Total IMS-AKA DEL-SA success responses sent"
        ::= { apSecuritySAIMSAKAStats  14 }

    apSecSAIMSAKADelSuccessRespRcvd OBJECT-TYPE
        SYNTAX          Counter32
        MAX-ACCESS      read-only
        STATUS          current
        DESCRIPTION
           "Total IMS-AKA DEL-SA success responses received"
        ::= { apSecuritySAIMSAKAStats  15 }

    apSecSAIMSAKADelFailRespSent OBJECT-TYPE
        SYNTAX          Counter32
        MAX-ACCESS      read-only
        STATUS          current
        DESCRIPTION
           "Total IMS-AKA DEL-SA fail responses sent"
        ::= { apSecuritySAIMSAKAStats  16 }

    apSecSAIMSAKADelFailInvalidParamRespSent OBJECT-TYPE
        SYNTAX          Counter32
        MAX-ACCESS      read-only
        STATUS          current
        DESCRIPTION
           "Total IMS-AKA DEL-SA fail messages sent due to invalid parameter"
        ::= { apSecuritySAIMSAKAStats  17 }

    apSecSAIMSAKADelFailRespRcvd OBJECT-TYPE
        SYNTAX          Counter32
        MAX-ACCESS      read-only
        STATUS          current
        DESCRIPTION
           "Total IMS-AKA DEL-SA fail responses received"
        ::= { apSecuritySAIMSAKAStats  18 }

    apSecSAIMSAKADelTransactionTimeout OBJECT-TYPE
        SYNTAX          Counter32
        MAX-ACCESS      read-only
        STATUS          current
        DESCRIPTION
           "Total IMS-AKA DEL-SA messages resulting from transaction timeouts"
        ::= { apSecuritySAIMSAKAStats  19 }

    apSecSAIMSAKADelDueToTimeout OBJECT-TYPE
        SYNTAX          Counter32
        MAX-ACCESS      read-only
        STATUS          current
        DESCRIPTION
           "Total IMS-AKA DEL-SA messages resulting from timeouts"
        ::= { apSecuritySAIMSAKAStats  20 }

    apSecSAIMSAKAModReqSent OBJECT-TYPE
        SYNTAX          Counter32
        MAX-ACCESS      read-only
        STATUS          current
        DESCRIPTION
           "Total IMS-AKA MOD-SA requests sent"
        ::= { apSecuritySAIMSAKAStats  21 }

    apSecSAIMSAKAModReqRcvd OBJECT-TYPE
        SYNTAX          Counter32
        MAX-ACCESS      read-only
        STATUS          current
        DESCRIPTION
           "Total IMS-AKA MOD-SA requests received"
        ::= { apSecuritySAIMSAKAStats  22 }

    apSecSAIMSAKAModSuccessRespSent OBJECT-TYPE
        SYNTAX          Counter32
        MAX-ACCESS      read-only
        STATUS          current
        DESCRIPTION
           "Total IMS-AKA MOD-SA success responses sent"
        ::= { apSecuritySAIMSAKAStats  23 }

    apSecSAIMSAKAModSuccessRespRcvd OBJECT-TYPE
        SYNTAX          Counter32
        MAX-ACCESS      read-only
        STATUS          current
        DESCRIPTION
           "Total IMS-AKA MOD-SA success responses received"
        ::= { apSecuritySAIMSAKAStats  24 }

    apSecSAIMSAKAModFailRespSent OBJECT-TYPE
        SYNTAX          Counter32
        MAX-ACCESS      read-only
        STATUS          current
        DESCRIPTION
           "Total IMS-AKA MOD-SA fail responses sent"
        ::= { apSecuritySAIMSAKAStats  25 }

    apSecSAIMSAKAModFailInvalidParamRespSent OBJECT-TYPE
        SYNTAX          Counter32
        MAX-ACCESS      read-only
        STATUS          current
        DESCRIPTION
           "Total IMS-AKA MOD-SA fail messages sent due to invalid parameter"
        ::= { apSecuritySAIMSAKAStats  26 }

    apSecSAIMSAKAModFailRespRcvd OBJECT-TYPE
        SYNTAX          Counter32
        MAX-ACCESS      read-only
        STATUS          current
        DESCRIPTION
           "Total IMS-AKA MOD-SA fail responses received"
        ::= { apSecuritySAIMSAKAStats  27 }

    apSecSAIMSAKAModTransactionTimeout OBJECT-TYPE
        SYNTAX          Counter32
        MAX-ACCESS      read-only
        STATUS          current
        DESCRIPTION
           "Total IMS-AKA MOD-SA messages resulting from transaction timeouts"
        ::= { apSecuritySAIMSAKAStats  28 }

    apSecSAIMSAKASaCreated OBJECT-TYPE
        SYNTAX          Counter32
        MAX-ACCESS      read-only
        STATUS          current
        DESCRIPTION
           "Total number of IMS-AKA SA added"
        ::= { apSecuritySAIMSAKAStats  29 }

    apSecSAIMSAKASaCreatedInboundSent OBJECT-TYPE
        SYNTAX          Counter32
        MAX-ACCESS      read-only
        STATUS          current
        DESCRIPTION
           "Total IMS-AKA SA added in inbound"
        ::= { apSecuritySAIMSAKAStats  30 }

    apSecSAIMSAKASaCreatedOutboundSent OBJECT-TYPE
        SYNTAX          Counter32
        MAX-ACCESS      read-only
        STATUS          current
        DESCRIPTION
           "Total IMS-AKA SA added in outbound"
        ::= { apSecuritySAIMSAKAStats  31 }

    apSecSAIMSAKASaCreateFailed OBJECT-TYPE
        SYNTAX          Counter32
        MAX-ACCESS      read-only
        STATUS          current
        DESCRIPTION
           "Total IMS-AKA SA addition failed"
        ::= { apSecuritySAIMSAKAStats  32 }

    apSecSAIMSAKASaCreatePPMInboundFailed OBJECT-TYPE
        SYNTAX          Counter32
        MAX-ACCESS      read-only
        STATUS          current
        DESCRIPTION
           "Total IMS-AKA SA Add inbound PPM failed"
        ::= { apSecuritySAIMSAKAStats  33 }

    apSecSAIMSAKASaCreatePPMOutboundFailed OBJECT-TYPE
        SYNTAX          Counter32
        MAX-ACCESS      read-only
        STATUS          current
        DESCRIPTION
           "Total IMS-AKA SA Add outbound PPM failed"
        ::= { apSecuritySAIMSAKAStats  34 }

    apSecSAIMSAKASaDeleted OBJECT-TYPE
        SYNTAX          Counter32
        MAX-ACCESS      read-only
        STATUS          current
        DESCRIPTION
           "Total number of IMS-AKA SA deleted"
        ::= { apSecuritySAIMSAKAStats  35 }

    apSecSAIMSAKASaDeletedInboundSent OBJECT-TYPE
        SYNTAX          Counter32
        MAX-ACCESS      read-only
        STATUS          current
        DESCRIPTION
           "Total number of IMS-AKA SA deleted in the inbound"
        ::= { apSecuritySAIMSAKAStats  36 }

    apSecSAIMSAKASaDeletedOutboundSent OBJECT-TYPE
        SYNTAX          Counter32
        MAX-ACCESS      read-only
        STATUS          current
        DESCRIPTION
           "Total number of IMS-AKA SA deleted in the outbound"
        ::= { apSecuritySAIMSAKAStats  37 }

    apSecSAIMSAKASaDelFailed OBJECT-TYPE
        SYNTAX          Counter32
        MAX-ACCESS      read-only
        STATUS          current
        DESCRIPTION
           "Total number of IMS-AKA SA Delete failed"
        ::= { apSecuritySAIMSAKAStats  38 }

    apSecSAIMSAKASaDelPPMInboundFailed OBJECT-TYPE
        SYNTAX          Counter32
        MAX-ACCESS      read-only
        STATUS          current
        DESCRIPTION
           "Total number of IMS-AKA SA Delete inbound PPM failed"
        ::= { apSecuritySAIMSAKAStats  39 }

    apSecSAIMSAKASaDelPPMOutboundFailed OBJECT-TYPE
        SYNTAX          Counter32
        MAX-ACCESS      read-only
        STATUS          current
        DESCRIPTION
           "Total number of IMS-AKA SA Delete outbound PPM failed"
        ::= { apSecuritySAIMSAKAStats  40 }

    apSecSAIMSAKASaDelFailAddrMaskMismatch OBJECT-TYPE
        SYNTAX          Counter32
        MAX-ACCESS      read-only
        STATUS          current
        DESCRIPTION
           "Total number of IMS-AKA SA Delete failed due to address mask mismatch"
        ::= { apSecuritySAIMSAKAStats  41 }

    apSecSAIMSAKASaDelFailProtoParamsInvalid OBJECT-TYPE
        SYNTAX          Counter32
        MAX-ACCESS      read-only
        STATUS          current
        DESCRIPTION
           "Total number of IMS-AKA SA Delete failed due to invalid protocol parameters"
        ::= { apSecuritySAIMSAKAStats  42 }

    apSecSAIMSAKASaDelFailProtoDataInvalid OBJECT-TYPE
        SYNTAX          Counter32
        MAX-ACCESS      read-only
        STATUS          current
        DESCRIPTION
           "Total number of IMS-AKA SA Delete failed due to invalid protocol data"
        ::= { apSecuritySAIMSAKAStats  43 }

    apSecSAIMSAKASaCollision OBJECT-TYPE
        SYNTAX          Counter32
        MAX-ACCESS      read-only
        STATUS          current
        DESCRIPTION
           "Total number of IMS-AKA SA collisions"
        ::= { apSecuritySAIMSAKAStats  44 }

    apSecSAIMSAKASaCollisionRecoveryFail OBJECT-TYPE
        SYNTAX          Counter32
        MAX-ACCESS      read-only
        STATUS          current
        DESCRIPTION
           "Total number of IMS-AKA SA collision recovery failed"
        ::= { apSecuritySAIMSAKAStats  45 }

    apSecSAIMSAKASaCollisionRecoverySuccess OBJECT-TYPE
        SYNTAX          Counter32
        MAX-ACCESS      read-only
        STATUS          current
        DESCRIPTION
           "Total number of IMS-AKA SA collision recovery successful"
        ::= { apSecuritySAIMSAKAStats  46 }

    apSecSAIMSAKASaCollisionRecoveryLkupFail OBJECT-TYPE
        SYNTAX          Counter32
        MAX-ACCESS      read-only
        STATUS          current
        DESCRIPTION
           "Total number of IMS-AKA SA collisions recovery lookup failed"
        ::= { apSecuritySAIMSAKAStats  47 }

    apSecSAIMSAKASaKeyNotFound OBJECT-TYPE
        SYNTAX          Counter32
        MAX-ACCESS      read-only
        STATUS          current
        DESCRIPTION
           "Total number of IMS-AKA SA key not found event"
        ::= { apSecuritySAIMSAKAStats  48 }

    apSecSAIMSAKASaKeyNotFoundTimeout OBJECT-TYPE
        SYNTAX          Counter32
        MAX-ACCESS      read-only
        STATUS          current
        DESCRIPTION
           "Total number of IMS-AKA SA key not found timeout event"
        ::= { apSecuritySAIMSAKAStats  49 }

    apSecSAIMSAKASaKeyExists OBJECT-TYPE
        SYNTAX          Counter32
        MAX-ACCESS      read-only
        STATUS          current
        DESCRIPTION
           "Total number of IMS-AKA SA key exists event"
        ::= { apSecuritySAIMSAKAStats  50 }

    apSecSAIMSAKASaRecovery OBJECT-TYPE
        SYNTAX          Counter32
        MAX-ACCESS      read-only
        STATUS          current
        DESCRIPTION
           "Total number of IMS-AKA SA recovery event"
        ::= { apSecuritySAIMSAKAStats  51 }

    apSecSAIMSAKASaRecoveryFail OBJECT-TYPE
        SYNTAX          Counter32
        MAX-ACCESS      read-only
        STATUS          current
        DESCRIPTION
           "Total number of IMS-AKA SA recovery fail event"
        ::= { apSecuritySAIMSAKAStats  52 }

    apSecSAIMSAKASaTransactionQueue OBJECT-TYPE
        SYNTAX          Counter32
        MAX-ACCESS      read-only
        STATUS          current
        DESCRIPTION
           "Total count of IMS-AKA SA trans queue"
        ::= { apSecuritySAIMSAKAStats  53 }

    apSecSAIMSAKASaRedundancySyncQueue OBJECT-TYPE
        SYNTAX          Counter32
        MAX-ACCESS      read-only
        STATUS          current
        DESCRIPTION
           "Total count of IMS-AKA SA redundancy queue"
        ::= { apSecuritySAIMSAKAStats  54 }

    apSecSAIMSAKASaInboundOnly OBJECT-TYPE
        SYNTAX          Counter32
        MAX-ACCESS      read-only
        STATUS          current
        DESCRIPTION
           "Total count of IMS-AKA SA inbound record"
        ::= { apSecuritySAIMSAKAStats  55 }

    apSecSAIMSAKASaOutboundOnly OBJECT-TYPE
        SYNTAX          Counter32
        MAX-ACCESS      read-only
        STATUS          current
        DESCRIPTION
           "Total count of IMS-AKA SA outbound record"
        ::= { apSecuritySAIMSAKAStats  56 }

    apSecSAIMSAKAAddFailInvalidTimer OBJECT-TYPE
        SYNTAX          Counter32
        MAX-ACCESS      read-only
        STATUS          current
        DESCRIPTION
           "Total number of times IMS-AKA SA invalid timer event occurred"
        ::= { apSecuritySAIMSAKAStats  57 }

    apSecSAIMSAKAAddFailTableInsertFail OBJECT-TYPE
        SYNTAX          Counter32
        MAX-ACCESS      read-only
        STATUS          current
        DESCRIPTION
           "Total number of times IMS-AKA SA add in table failed"
        ::= { apSecuritySAIMSAKAStats  58 }

    apSecSAIMSAKASendAddToRed OBJECT-TYPE
        SYNTAX          Counter32
        MAX-ACCESS      read-only
        STATUS          current
        DESCRIPTION
           "Total number of times IMS-AKA SA sent ADD event to redundant peer"
        ::= { apSecuritySAIMSAKAStats  59 }

    apSecSAIMSAKASendModToRed OBJECT-TYPE
        SYNTAX          Counter32
        MAX-ACCESS      read-only
        STATUS          current
        DESCRIPTION
           "Total number of times IMS-AKA SA sent MODIFY event to redundant peer"
        ::= { apSecuritySAIMSAKAStats  60 }

    apSecSAIMSAKARcvdAddFromActive OBJECT-TYPE
        SYNTAX          Counter32
        MAX-ACCESS      read-only
        STATUS          current
        DESCRIPTION
           "Total number of times IMS-AKA SA received ADD event from active"
        ::= { apSecuritySAIMSAKAStats  61 }

    apSecSAIMSAKARcvdModFromActive OBJECT-TYPE
        SYNTAX          Counter32
        MAX-ACCESS      read-only
        STATUS          current
        DESCRIPTION
           "Total number of times IMS-AKA SA received MODIFY event from active"
        ::= { apSecuritySAIMSAKAStats  62 }

    apSecSAIMSAKASaRedAddRecFailure OBJECT-TYPE
        SYNTAX          Counter32
        MAX-ACCESS      read-only
        STATUS          current
        DESCRIPTION
           "Total number of IMS-AKA SA ADD to redundancy queue failed"
        ::= { apSecuritySAIMSAKAStats  63 }

    apSecSAIMSAKAInvalidRedAction OBJECT-TYPE
        SYNTAX          Counter32
        MAX-ACCESS      read-only
        STATUS          current
        DESCRIPTION
           "Total number of IMS-AKA invalid redundant actions"
        ::= { apSecuritySAIMSAKAStats  64 }

    apSecSAIMSAKASendTimedDelToRed OBJECT-TYPE
        SYNTAX          Counter32
        MAX-ACCESS      read-only
        STATUS          current
        DESCRIPTION
           "Total number of times IMS-AKA Timed Delete event sent to redundant peer"
        ::= { apSecuritySAIMSAKAStats  65 }

    apSecSAIMSAKARcvdTimedDelFromAct OBJECT-TYPE
        SYNTAX          Counter32
        MAX-ACCESS      read-only
        STATUS          current
        DESCRIPTION
           "Total number of times IMS-AKA Timed Delete event received from active"
        ::= { apSecuritySAIMSAKAStats  66 }

    apSecSAIMSAKASAAgentSAReqTransQueueSize OBJECT-TYPE
        SYNTAX          Gauge32
        MAX-ACCESS      read-only
        STATUS          current
        DESCRIPTION
           "SA request transaction queue size of the security association agent"
        ::= { apSecuritySAIMSAKAStats  67 }

    apSecSAIMSAKASAAgentAllowTransQuota OBJECT-TYPE
        SYNTAX          Gauge32
        MAX-ACCESS      read-only
        STATUS          current
        DESCRIPTION
           "Allowed transaction quota of the security association agent"
        ::= { apSecuritySAIMSAKAStats  68 }

    apSecSAIMSAKASAAgentDelayDeleteCount OBJECT-TYPE
        SYNTAX          Counter32
        MAX-ACCESS      read-only
        STATUS          current
        DESCRIPTION
           "Delay delete count of the security association agent"
        ::= { apSecuritySAIMSAKAStats  69 }

    apSecSAIMSAKASAAgentMaxTransQueueSize OBJECT-TYPE
        SYNTAX          Counter32
        MAX-ACCESS      read-only
        STATUS          current
        DESCRIPTION
           "Maximum transaction queue size of the security association agent"
        ::= { apSecuritySAIMSAKAStats  70 }

    apSecSAIMSAKARegsTotal OBJECT-TYPE
        SYNTAX          Counter32
        MAX-ACCESS      read-only
        STATUS          current
        DESCRIPTION
           "Total number of registration messages received"
        ::= { apSecuritySAIMSAKAStats  71 }

    apSecSAIMSAKARegsFromUnprotPort OBJECT-TYPE
        SYNTAX          Counter32
        MAX-ACCESS      read-only
        STATUS          current
        DESCRIPTION
           "Total number of unprotected registration messages received"
        ::= { apSecuritySAIMSAKAStats  72 }

    apSecSAIMSAKARegsFromUnprotPortBeforeExpiry OBJECT-TYPE
        SYNTAX          Counter32
        MAX-ACCESS      read-only
        STATUS          current
        DESCRIPTION
           "Total number of unprotected registration messages received before expiry"
        ::= { apSecuritySAIMSAKAStats  73 }

    apSecSAIMSAKARegsInProtPortPriorDisconnect OBJECT-TYPE
        SYNTAX          Counter32
        MAX-ACCESS      read-only
        STATUS          current
        DESCRIPTION
           "Total number of prior disconnects on the inbound"
        ::= { apSecuritySAIMSAKAStats  74 }

    apSecSAIMSAKARegsOutProtPortPriorDisconnect OBJECT-TYPE
        SYNTAX          Counter32
        MAX-ACCESS      read-only
        STATUS          current
        DESCRIPTION
           "Total number of prior disconnects on the outbound"
        ::= { apSecuritySAIMSAKAStats  75 }

    apSecSAIMSAKAAnswerBeforeChallenge OBJECT-TYPE
        SYNTAX          Counter32
        MAX-ACCESS      read-only
        STATUS          current
        DESCRIPTION
           "Total number of registration answer messages received before challenge"
        ::= { apSecuritySAIMSAKAStats  76 }

    apSecSAIMSAKARegsFromPotectedPort OBJECT-TYPE
        SYNTAX          Counter32
        MAX-ACCESS      read-only
        STATUS          current
        DESCRIPTION
           "Total number of protected registration messages received"
        ::= { apSecuritySAIMSAKAStats  77 }

    apSecSAIMSAKARegsInitRegRejectBusy OBJECT-TYPE
        SYNTAX          Counter32
        MAX-ACCESS      read-only
        STATUS          current
        DESCRIPTION
           "Total number of initial registration messages rejected with busy error code"
        ::= { apSecuritySAIMSAKAStats  78 }

    apSecSAIMSAKARegsInitRegRejectResource OBJECT-TYPE
        SYNTAX          Counter32
        MAX-ACCESS      read-only
        STATUS          current
        DESCRIPTION
           "Total number of initial registration messages rejected because of resource unavailability"
        ::= { apSecuritySAIMSAKAStats  79 }

    apSecSAIMSAKARegsInitRegFailedAllocIms OBJECT-TYPE
        SYNTAX          Counter32
        MAX-ACCESS      read-only
        STATUS          current
        DESCRIPTION
           "Total number of initial registration messages rejected because of memory allocation failure"
        ::= { apSecuritySAIMSAKAStats  80 }

    apSecSAIMSAKARegsInitRegImsExist OBJECT-TYPE
        SYNTAX          Counter32
        MAX-ACCESS      read-only
        STATUS          current
        DESCRIPTION
           "Total number of initial registration messages for which IMS entry already exists"
        ::= { apSecuritySAIMSAKAStats  81 }

    apSecSAIMSAKARegsInitRegFailedSecurityHeader OBJECT-TYPE
        SYNTAX          Counter32
        MAX-ACCESS      read-only
        STATUS          current
        DESCRIPTION
           "Total number of initial registration messages received with bad security header"
        ::= { apSecuritySAIMSAKAStats  82 }

    apSecSAIMSAKARegsInitRegPassedQuota OBJECT-TYPE
        SYNTAX          Counter32
        MAX-ACCESS      read-only
        STATUS          current
        DESCRIPTION
           "Total number of initial registration messages that passed the quota"
        ::= { apSecuritySAIMSAKAStats  83 }

    apSecSAIMSAKARegsReRegRejectBusy OBJECT-TYPE
        SYNTAX          Counter32
        MAX-ACCESS      read-only
        STATUS          current
        DESCRIPTION
           "Total number of re-registration messages rejected with busy error code"
        ::= { apSecuritySAIMSAKAStats  84 }

    apSecSAIMSAKARegsReRegRejectResource OBJECT-TYPE
        SYNTAX          Counter32
        MAX-ACCESS      read-only
        STATUS          current
        DESCRIPTION
           "Total number of re-registration messages rejected because of resource unavailability"
        ::= { apSecuritySAIMSAKAStats  85 }

    apSecSAIMSAKARegsReRegFailedSecurityHeader OBJECT-TYPE
        SYNTAX          Counter32
        MAX-ACCESS      read-only
        STATUS          current
        DESCRIPTION
           "Total number of re-registration messages received with bad security header"
        ::= { apSecuritySAIMSAKAStats  86 }

    apSecSAIMSAKARegsReRegNoImsEntry OBJECT-TYPE
        SYNTAX          Counter32
        MAX-ACCESS      read-only
        STATUS          current
        DESCRIPTION
           "Total number of re-registration messages for which no IMS entry exists"
        ::= { apSecuritySAIMSAKAStats  87 }

    apSecSAIMSAKARegsReRegPassedQuota OBJECT-TYPE
        SYNTAX          Counter32
        MAX-ACCESS      read-only
        STATUS          current
        DESCRIPTION
           "Total number of re-registration messages that passed the quota"
        ::= { apSecuritySAIMSAKAStats  88 }

    apSecSAIMSAKARegForwardUnProtectReg OBJECT-TYPE
        SYNTAX          Counter32
        MAX-ACCESS      read-only
        STATUS          current
        DESCRIPTION
           "Total number of unprotected re-registration messages that were forwarded"
        ::= { apSecuritySAIMSAKAStats  89 }

    apSecSAIMSAKAReuseSpiFalse OBJECT-TYPE
        SYNTAX          Counter32
        MAX-ACCESS      read-only
        STATUS          current
        DESCRIPTION
           "Total number of re-registration messages for which re-use SPI is false"
        ::= { apSecuritySAIMSAKAStats  90 }

    apSecSAIMSAKAReuseSpiTrue OBJECT-TYPE
        SYNTAX          Counter32
        MAX-ACCESS      read-only
        STATUS          current
        DESCRIPTION
           "Total number of re-registration messages for which re-use SPI is true"
        ::= { apSecuritySAIMSAKAStats  91 }

    apSecSAIMSAKAIncompleteReg OBJECT-TYPE
        SYNTAX          Counter32
        MAX-ACCESS      read-only
        STATUS          current
        DESCRIPTION
           "Total number of re-registration messages resulting in incomplete registration"
        ::= { apSecuritySAIMSAKAStats  92 }
 
    -- SA SRTP STATS
    apSecuritySASRTPStats OBJECT IDENTIFIER ::= { apSecuritySAMIBObjects 3 }
 
    apSecSASRTPAddReqSent OBJECT-TYPE
        SYNTAX          Counter32
        MAX-ACCESS      read-only
        STATUS          current
        DESCRIPTION
           "Total number of SRTP SA ADD requests sent"
        ::= { apSecuritySASRTPStats  1 }

    apSecSASRTPAddReqRcvd OBJECT-TYPE
        SYNTAX          Counter32
        MAX-ACCESS      read-only
        STATUS          current
        DESCRIPTION
           "Total number of SRTP SA ADD requests received"
        ::= { apSecuritySASRTPStats  2 }

    apSecSASRTPAddSuccessRespSent OBJECT-TYPE
        SYNTAX          Counter32
        MAX-ACCESS      read-only
        STATUS          current
        DESCRIPTION
           "Total SRTP ADD-SA success responses sent"
        ::= { apSecuritySASRTPStats  3 }

    apSecSASRTPAddSuccessRespRcvd OBJECT-TYPE
        SYNTAX          Counter32
        MAX-ACCESS      read-only
        STATUS          current
        DESCRIPTION
           "Total SRTP ADD-SA success response received"
        ::= { apSecuritySASRTPStats  4 }

    apSecSASRTPAddFailRespSent OBJECT-TYPE
        SYNTAX          Counter32
        MAX-ACCESS      read-only
        STATUS          current
        DESCRIPTION
           "Total SRTP ADD-SA fail responses sent"
        ::= { apSecuritySASRTPStats  5 }

    apSecSASRTPAddFailRespRcvd OBJECT-TYPE
        SYNTAX          Counter32
        MAX-ACCESS      read-only
        STATUS          current
        DESCRIPTION
           "Total SRTP ADD-SA fail responses received"
        ::= { apSecuritySASRTPStats  6 }

    apSecSASRTPAddTransactionTimeout OBJECT-TYPE
        SYNTAX          Counter32
        MAX-ACCESS      read-only
        STATUS          current
        DESCRIPTION
           "Total SRTP ADD-SA transaction timeouts"
        ::= { apSecuritySASRTPStats  7 }

    apSecSASRTPDelReqSent OBJECT-TYPE
        SYNTAX          Counter32
        MAX-ACCESS      read-only
        STATUS          current
        DESCRIPTION
           "Total SRTP DEL-SA requests sent"
        ::= { apSecuritySASRTPStats  8 }

    apSecSASRTPDelReqRcvd OBJECT-TYPE
        SYNTAX          Counter32
        MAX-ACCESS      read-only
        STATUS          current
        DESCRIPTION
           "Total SRTP DEL-SA requests received"
        ::= { apSecuritySASRTPStats  9 }

    apSecSASRTPDelSuccessRespSent OBJECT-TYPE
        SYNTAX          Counter32
        MAX-ACCESS      read-only
        STATUS          current
        DESCRIPTION
           "Total SRTP DEL-SA success responses sent"
        ::= { apSecuritySASRTPStats  10 }

    apSecSASRTPDelSuccessRespRcvd OBJECT-TYPE
        SYNTAX          Counter32
        MAX-ACCESS      read-only
        STATUS          current
        DESCRIPTION
           "Total SRTP DEL-SA success responses received"
        ::= { apSecuritySASRTPStats  11 }

    apSecSASRTPDelFailRespSent OBJECT-TYPE
        SYNTAX          Counter32
        MAX-ACCESS      read-only
        STATUS          current
        DESCRIPTION
           "Total SRTP DEL-SA fail responses sent"
        ::= { apSecuritySASRTPStats  12 }

    apSecSASRTPDelFailRespRcvd OBJECT-TYPE
        SYNTAX          Counter32
        MAX-ACCESS      read-only
        STATUS          current
        DESCRIPTION
           "Total SRTP DEL-SA fail responses received"
        ::= { apSecuritySASRTPStats  13 }

    apSecSASRTPDelTransactionTimeout OBJECT-TYPE
        SYNTAX          Counter32
        MAX-ACCESS      read-only
        STATUS          current
        DESCRIPTION
           "Total SRTP DEL-SA transaction timeouts"
        ::= { apSecuritySASRTPStats  14 }

    apSecSASRTPModReqSent OBJECT-TYPE
        SYNTAX          Counter32
        MAX-ACCESS      read-only
        STATUS          current
        DESCRIPTION
           "Total SRTP MOD-SA requests sent"
        ::= { apSecuritySASRTPStats  15 }

    apSecSASRTPModReqRcvd OBJECT-TYPE
        SYNTAX          Counter32
        MAX-ACCESS      read-only
        STATUS          current
        DESCRIPTION
           "Total SRTP MOD-SA requests received"
        ::= { apSecuritySASRTPStats  16 }

    apSecSASRTPModSuccessRespSent OBJECT-TYPE
        SYNTAX          Counter32
        MAX-ACCESS      read-only
        STATUS          current
        DESCRIPTION
           "Total SRTP MOD-SA success response sent"
        ::= { apSecuritySASRTPStats  17 }

    apSecSASRTPModSuccessRespRcvd OBJECT-TYPE
        SYNTAX          Counter32
        MAX-ACCESS      read-only
        STATUS          current
        DESCRIPTION
           "Total SRTP MOD-SA success responses received"
        ::= { apSecuritySASRTPStats  18 }

    apSecSASRTPModFailRespSent OBJECT-TYPE
        SYNTAX          Counter32
        MAX-ACCESS      read-only
        STATUS          current
        DESCRIPTION
           "Total SRTP MOD-SA fail responses sent"
        ::= { apSecuritySASRTPStats  19 }

    apSecSASRTPModFailRespRcvd OBJECT-TYPE
        SYNTAX          Counter32
        MAX-ACCESS      read-only
        STATUS          current
        DESCRIPTION
           "Total SRTP MOD-SA fail responses received"
        ::= { apSecuritySASRTPStats  20 }

    apSecSASRTPModTransactionTimeout OBJECT-TYPE
        SYNTAX          Counter32
        MAX-ACCESS      read-only
        STATUS          current
        DESCRIPTION
           "Total SRTP MOD-SA transaction timeouts"
        ::= { apSecuritySASRTPStats  21 }

    apSecSASRTPSaCreated OBJECT-TYPE
        SYNTAX          Counter32
        MAX-ACCESS      read-only
        STATUS          current
        DESCRIPTION
           "Total SRTP SA added"
        ::= { apSecuritySASRTPStats  22 }

    apSecSASRTPSaCreateFailed OBJECT-TYPE
        SYNTAX          Counter32
        MAX-ACCESS      read-only
        STATUS          current
        DESCRIPTION
           "Total SRTP SA add failed"
        ::= { apSecuritySASRTPStats  23 }

    apSecSASRTPSaDeleted OBJECT-TYPE
        SYNTAX          Counter32
        MAX-ACCESS      read-only
        STATUS          current
        DESCRIPTION
           "Total SRTP SA deleted"
        ::= { apSecuritySASRTPStats  24 }

    apSecSASRTPSaDeleteFailed OBJECT-TYPE
        SYNTAX          Counter32
        MAX-ACCESS      read-only
        STATUS          current
        DESCRIPTION
           "Total SRTP SA delete failed"
        ::= { apSecuritySASRTPStats  25 }

    apSecSASRTPSaCollision OBJECT-TYPE
        SYNTAX          Counter32
        MAX-ACCESS      read-only
        STATUS          current
        DESCRIPTION
           "Total SRTP SA collision"
        ::= { apSecuritySASRTPStats  26 }

    apSecSASRTPSaKeyNotFound OBJECT-TYPE
        SYNTAX          Counter32
        MAX-ACCESS      read-only
        STATUS          current
        DESCRIPTION
           "Total SRTP SA key not found event"
        ::= { apSecuritySASRTPStats  27 }

    apSecurityNotificationObjects OBJECT IDENTIFIER ::= { apSecurityModule 2 }	 

    apSecuritySpi OBJECT-TYPE
	SYNTAX		Unsigned32
	MAX-ACCESS	accessible-for-notify
	STATUS		current
	DESCRIPTION	"Tunnel security-policy-index."

	::= { apSecurityNotificationObjects 1 }
	
    apSecuritySrcIpAddress 	OBJECT-TYPE
	SYNTAX		IpAddress
	MAX-ACCESS	accessible-for-notify
	STATUS		current
	DESCRIPTION
	    "Source IP address."
	::= { apSecurityNotificationObjects 2 }

    apSecurityDstIpAddress 	OBJECT-TYPE
	SYNTAX		IpAddress
	MAX-ACCESS	accessible-for-notify
	STATUS		current
	DESCRIPTION
	    "Destination IP address."
	::= { apSecurityNotificationObjects 3 }

    apSecurityIPSECMode		OBJECT-TYPE
	SYNTAX     	     	INTEGER {
					tunnel(0),
					transport(1)
				}
	MAX-ACCESS		accessible-for-notify
	STATUS	   		current
	DESCRIPTION
	"IPSec mode."
	::= { apSecurityNotificationObjects 4 }

    apSecurityEncryptionAlg	OBJECT-TYPE
	SYNTAX     	     	INTEGER {
					any(0),
					alg-des(1),
					alg-3des(2),
					alg-blowfish(3),
					alg-aes(4),
					null(5)
				}
	MAX-ACCESS		accessible-for-notify
	STATUS	   		current
	DESCRIPTION
	"Type of the encryption algorithms supported in the tunnel setup."
	::= { apSecurityNotificationObjects 5 }
	
    apSecurityAuthAlg		OBJECT-TYPE
	SYNTAX     	     	INTEGER {
					any(0),
					md5(1),
					sha1(2)
				}
	MAX-ACCESS		accessible-for-notify
	STATUS	   		current
	DESCRIPTION
	"Type of the authentication algorithms supported in the tunnel setup."
	::= { apSecurityNotificationObjects 6 }

    apSecuritySecProtocol	OBJECT-TYPE
	SYNTAX     	     	INTEGER {
					ah(0),
					esp(1),
					esp-auth(2),
					esp-null(3)
				}
	MAX-ACCESS		accessible-for-notify
	STATUS	   		current
	DESCRIPTION
	"Type of the security protocol supported in the tunnel setup."
	::= { apSecurityNotificationObjects 7 }

    apSecurityFailureCause	OBJECT-TYPE
	SYNTAX     	     	INTEGER {
					incorrect-id(0),
					incorrect-user-passwd(1),
					incorrect-shared-secret(2),
					incorrect-dh-group(3),
					incorrect-encryption-alg(4),
					incorrect-auth-alg(5),
					incorrect-sec-protocol(6),
					incorrect-hash(7),
					incorrect-mode(8),
					service-unavailable(9),
					access-reject(10),
					initiator-timeout(11),
					invalid-certificate(12),
                                        authentication-failure(13),
                                        authorization-failure(14),
                                        accounting-failure(15)
				}
	MAX-ACCESS		accessible-for-notify
	STATUS	   		current
	DESCRIPTION
	"Reason for failure in the IKE, IPSec or RADIUS areas."
	::= { apSecurityNotificationObjects 8 }

    apSecurityFailureArea	OBJECT-TYPE
	SYNTAX     	     	INTEGER {
					ike(0),
					ipsec(1),
					radius(2),
					tacacs(3)
				}
	MAX-ACCESS		accessible-for-notify
	STATUS	   		current
	DESCRIPTION
	"Where the failure happened."
	::= { apSecurityNotificationObjects 9 }


    apSecurityStatus OBJECT-TYPE
	SYNTAX		INTEGER {
		       success (1),
		       failure (2)
		       }
	MAX-ACCESS	accessible-for-notify
	STATUS			current
	DESCRIPTION	"Status."

	::= { apSecurityNotificationObjects 10 }

    apSecurityDateTime      OBJECT-TYPE
	SYNTAX        DisplayString
	MAX-ACCESS    accessible-for-notify
	STATUS	      current
	DESCRIPTION   "Time as configured at the Net-Net SBC when an
			event completes."
	::= { apSecurityNotificationObjects 11 }
	
    apSecurityUser    OBJECT-TYPE
	SYNTAX        DisplayString  (SIZE (0..255))
	MAX-ACCESS    accessible-for-notify
	STATUS	      current
	DESCRIPTION   "User name" 
	::= { apSecurityNotificationObjects 12 }

    apSecurityPeerPort OBJECT-TYPE
	SYNTAX		InetPortNumber
	MAX-ACCESS	accessible-for-notify
	STATUS			current
	DESCRIPTION	"IKE peer port"

	::= { apSecurityNotificationObjects 13 }
	
    apSecurityPeerIpAddress 	OBJECT-TYPE
	SYNTAX		IpAddress
	MAX-ACCESS	accessible-for-notify
	STATUS		current
	DESCRIPTION
	    "IKE peer IP address."
	::= { apSecurityNotificationObjects 14 }

    apSecurityCRLServer      OBJECT-TYPE
	SYNTAX        DisplayString
	MAX-ACCESS    accessible-for-notify
	STATUS	      current
	DESCRIPTION   "CRL Server FQDN if configured."
	::= { apSecurityNotificationObjects 15 }

    apSecurityCRLRetrievalFailureCause	OBJECT-TYPE
	SYNTAX     	     	INTEGER {					
					internal(0),
					incorrect-response(1),
					timeout(2)
				}
	MAX-ACCESS		accessible-for-notify
	STATUS	   		current
	DESCRIPTION
	"Reason for failure in the CRL retrieval."
	::= { apSecurityNotificationObjects 16 }

    apSecurityLastSuccessfulCRLRetrieval OBJECT-TYPE
        SYNTAX          Integer32
        MAX-ACCESS      accessible-for-notify
        STATUS          current
        DESCRIPTION     
                "Last successful CRL retrieval."
        ::= { apSecurityNotificationObjects 17 }

    apSecurityCRLServerIPAddress	OBJECT-TYPE
	SYNTAX         	IpAddress	
      	MAX-ACCESS      accessible-for-notify
      	STATUS            current
      	DESCRIPTION
        	"CRL Server IP address."
	::= { apSecurityNotificationObjects 18 }

    apSecurityGTPProfileName      OBJECT-TYPE
        SYNTAX        DisplayString
        MAX-ACCESS    accessible-for-notify
        STATUS        current
        DESCRIPTION   "GTP Profile Name configured."
        ::= { apSecurityNotificationObjects 19 }

    apSecurityGTPHostName      OBJECT-TYPE
        SYNTAX        DisplayString
        MAX-ACCESS    accessible-for-notify
        STATUS        current
        DESCRIPTION   "GGSN/PGW Host Name if configured."
        ::= { apSecurityNotificationObjects 20 }

    apSecurityGTPLinkFailureCause  OBJECT-TYPE
        SYNTAX        INTEGER {                                       
				internal(0),                                    
				timeout(1),
				versionError(2)
                               }
        MAX-ACCESS    accessible-for-notify
        STATUS        current
        DESCRIPTION   "Reason for failure in the GTPCRL retrieval."
        ::= { apSecurityNotificationObjects 21 }

    apSecurityGTPIPAddress        OBJECT-TYPE
        SYNTAX        IpAddress      
        MAX-ACCESS    accessible-for-notify
        STATUS        current
        DESCRIPTION   "GGSN/PGW  IP address."
        ::= { apSecurityNotificationObjects 22 }

    apSecuritySrcAddressFamily 	OBJECT-TYPE
	SYNTAX		InetAddressType
	MAX-ACCESS	accessible-for-notify
	STATUS		current
	DESCRIPTION
	    "Source IP address family IPv4 or IPv6."
	::= { apSecurityNotificationObjects 23 }

    apSecuritySrcAddress 	OBJECT-TYPE
	SYNTAX		InetAddress
	MAX-ACCESS	accessible-for-notify
	STATUS		current
	DESCRIPTION
	    "Source IP address."
	::= { apSecurityNotificationObjects 24 }

    apSecurityDstAddressFamily 	OBJECT-TYPE
	SYNTAX		InetAddressType
	MAX-ACCESS	accessible-for-notify
	STATUS		current
	DESCRIPTION
	    "Destination IP address family IPv4 or IPv6."
	::= { apSecurityNotificationObjects 25 }

    apSecurityDstAddress 	OBJECT-TYPE
	SYNTAX		InetAddress
	MAX-ACCESS	accessible-for-notify
	STATUS		current
	DESCRIPTION
	    "Destination IP address."
	::= { apSecurityNotificationObjects 26 }

    apSecurityPeerAddressFamily 	OBJECT-TYPE
	SYNTAX		InetAddressType
	MAX-ACCESS	accessible-for-notify
	STATUS		current
	DESCRIPTION
	    "IKE peer IP address family IPv4 or IPv6."
	::= { apSecurityNotificationObjects 27 }

    apSecurityPeerAddress 	OBJECT-TYPE
	SYNTAX		InetAddress
	MAX-ACCESS	accessible-for-notify
	STATUS		current
	DESCRIPTION
	    "IKE peer IP address."
	::= { apSecurityNotificationObjects 28 }

    apSecurityTacacsDownLocalAuthUsed OBJECT-TYPE
        SYNTAX          DisplayString (SIZE (1..255))
        MAX-ACCESS      accessible-for-notify
        STATUS          current
        DESCRIPTION
            "The username that was authenticated locally by the system."
        ::= { apSecurityNotificationObjects 31 }
    
    apSecuritySrcPort OBJECT-TYPE
	SYNTAX		InetPortNumber
	MAX-ACCESS	accessible-for-notify
	STATUS			current
	DESCRIPTION	"Source/Client port of a secure connection"
	::= { apSecurityNotificationObjects 32 }
    
    apSecurityDstPort OBJECT-TYPE
	SYNTAX		InetPortNumber
	MAX-ACCESS	accessible-for-notify
	STATUS			current
	DESCRIPTION	"Destination/Server port of a secure connection"

	::= { apSecurityNotificationObjects 33 }

    apSecurityTlsSessionId OBJECT-TYPE
        SYNTAX        	OCTET STRING (SIZE(0..32))
	MAX-ACCESS	accessible-for-notify
	STATUS		current
	DESCRIPTION	"TLS session identifier octet string"

	::= { apSecurityNotificationObjects 34 }
    
    apSecurityTlsPacketFailureCount      OBJECT-TYPE
	SYNTAX		Counter32
        MAX-ACCESS    	accessible-for-notify
        STATUS        	current
        DESCRIPTION   	"Number of TLS packet failed to decrypt or encrypt"
        ::= { apSecurityNotificationObjects 35 }
   
    apSecurityTlsCipherSuite OBJECT-TYPE
	SYNTAX     	     	INTEGER {
				    tls-DHE-RSA-WITH-AES-256-GCM-SHA384(0),
				    tls-DHE-RSA-WITH-AES-256-CBC-SHA256(1),
				    tls-DHE-RSA-WITH-AES-256-CBC-SHA(2),
				    tls-RSA-WITH-AES-256-GCM-SHA384(3),
				    tls-RSA-WITH-AES-256-CBC-SHA256(4),
				    tls-RSA-WITH-AES-256-CBC-SHA(5),
				    tls-DHE-RSA-WITH-AES-128-GCM-SHA256(6),
				    tls-DHE-RSA-WITH-AES-128-CBC-SHA256(7),
				    tls-DHE-RSA-WITH-AES-128-CBC-SHA(8),
				    tls-RSA-WITH-AES-128-GCM-SHA256(9),
				    tls-RSA-WITH-AES-128-CBC-SHA256(10),
				    tls-RSA-WITH-AES-128-CBC-SHA(11),
				    tls-DHE-RSA-WITH-3DES-EDE-CBC-SHA(12),
				    tls-RSA-WITH-3DES-EDE-CBC-SHA(13),
				    tls-RSA-WITH-NULL-SHA256(14),
				    tls-RSA-WITH-NULL-SHA(15),
				    tls-RSA-WITH-NULL-MD5(16),
				    tls-ECDHE-ECDSA-WITH-AES-128-GCM-SHA256(17),
				    tls-ECDHE-ECDSA-WITH-AES-256-GCM-SHA384(18),
				    tls-ECDHE-RSA-WITH-AES-256-GCM-SHA384(19),
				    tls-ECDHE-RSA-WITH-AES-128-GCM-SHA256(20),
				    tls-ECDHE-RSA-WITH-AES-256-CBC-SHA384(21),
				    tls-ECDHE-RSA-WITH-AES-128-CBC-SHA256(22)
				}
	MAX-ACCESS		accessible-for-notify
	STATUS	   		current
	DESCRIPTION
	"List of supported TLS cipher suites."
	::= { apSecurityNotificationObjects 36 }
	
    apSecurityTlsDecryptionFailureCause	OBJECT-TYPE
	SYNTAX     	     	INTEGER {
					bad-mac-decode(0),
					bad-read-state(1),
					decryption-failed(2),
					decryption-failed-bad-record-mac(3),
					illegal-padding(4),
					packet-length-too-long(5),
					encrypted-length-too-long(6),
					record-too-small(7),
					record-length-too-short(8),
					block-cipher-pad-is-wrong(9)
				}
	MAX-ACCESS		accessible-for-notify
	STATUS	   		current
	DESCRIPTION
	"Reason for failure in the TLS decryption."
	::= { apSecurityNotificationObjects 37 }

    apSecurityTlsEncryptionFailureCause	OBJECT-TYPE
	SYNTAX     	     	INTEGER {
					bad-write-retry(0), 
					write-bio-not-set(1),
					bad-length(2),
					memory-alloc-failure(3)
				}
	MAX-ACCESS		accessible-for-notify
	STATUS	   		current
	DESCRIPTION
	"Reason for failure in the TLS encryption."
	::= { apSecurityNotificationObjects 38 }

    apSecuritySrtpEncryptionFailureCause	OBJECT-TYPE
	SYNTAX     	     	INTEGER {
					packet-too-small(0), 
					stream-not-found(1),
					key-expired(2),
					replay-old(3),
					replay-failed(4),
					auth-init-failed(5),
					stream-alloc-failed(6),
					encrypt-parse-error(7),
					cipher-failed(8),
					auth-failed(9)
				}
	MAX-ACCESS		accessible-for-notify
	STATUS	   		current
	DESCRIPTION
	"Reason for failure in the SRTP encryption."
	::= { apSecurityNotificationObjects 39 }
    
    apSecuritySrtpDecryptionFailureCause	OBJECT-TYPE
	SYNTAX     	     	INTEGER {
					packet-too-small(0), 
					stream-not-found(1),
					key-expired(2),
					replay-old(3),
					replay-failed(4),
					mki-changed(5),
					cipher-failed(6),
					auth-tag-failed(7),
					invalid-rtp-packet(8),
					auth-init-failed(9),
					decrypt-parse-error(10)
				}
	MAX-ACCESS		accessible-for-notify
	STATUS	   		current
	DESCRIPTION
	"Reason for failure in the SRTP decryption."
	::= { apSecurityNotificationObjects 40 }
    
    apSecuritySrtpEncrAlgorithm	OBJECT-TYPE
	SYNTAX     	     	INTEGER {
					null(0),
					aes-icm(1),
					aes-cbc(2),
					aes-gcm(3),
					aes-f8(4),
					aria-cm(5),
					aria-cbc(6)
				}
	MAX-ACCESS		accessible-for-notify
	STATUS	   		current
	DESCRIPTION
	"Type of the encryption algorithms supported by SRTP"
	::= { apSecurityNotificationObjects 41 }
    
    apSecuritySrtpAuthAlgorithm		OBJECT-TYPE
	SYNTAX     	     	INTEGER {
					null(0),
					hmac-sha1(1),
					hmac-md5(2)
				}
	MAX-ACCESS		accessible-for-notify
	STATUS	   		current
	DESCRIPTION
	"Type of the authentication algorithms supported by SRTP"
	::= { apSecurityNotificationObjects 42 }
    
-- Notifications

    apSecurityNotifications OBJECT IDENTIFIER ::= { apSecurityModule 3 }
    apSecurityAuthNotificationsPrefix
		OBJECT IDENTIFIER ::= { apSecurityNotifications 1 }
    apSecurityAuthNotifications
		OBJECT IDENTIFIER ::= { apSecurityAuthNotificationsPrefix 0 }

    apSecurityTunnelFailureNotification	NOTIFICATION-TYPE
	OBJECTS		{
			apSecuritySpi,
			apSecuritySrcIpAddress,
			apSecurityDstIpAddress,
			apSecurityFailureCause,
			apSecurityFailureArea,
			apSecurityStatus
			}
	STATUS	   	current
	DESCRIPTION
	      "The notification will be generated whenever IPSEC IKEV2 tunnel fails to 
	      establish. "
	::= { apSecurityAuthNotifications 1 }

    apSecurityRadiusFailureNotification	NOTIFICATION-TYPE
	OBJECTS		{
			apSecurityUser,
			apSecurityFailureCause,
			apSecurityFailureArea,
			apSecurityStatus
			}
	STATUS	   	current
	DESCRIPTION
	      "The notification will be generated whenever Radius authentication request fails."
	::= { apSecurityAuthNotifications 2 }

    apSecurityAuthFailureThresholdNotification	NOTIFICATION-TYPE
	OBJECTS		{
	                apSecurityUser,
			apSecurityPeerIpAddress,
			apSecurityPeerPort
			}
	STATUS	   	current
	DESCRIPTION
	      "The notification will be generated when IKE DDos auth-failure-threshold is reached and
	      report mode includes SNMP trap"
	::= { apSecurityAuthNotifications 3 }

    apSecurityTacacsFailureNotification	NOTIFICATION-TYPE
	OBJECTS		{
			apSecurityUser,
			apSecurityFailureCause,
			apSecurityFailureArea,
			apSecurityStatus
			}
	STATUS	   	current
	DESCRIPTION
	      "The notification will be generated whenever TACACS authentication requests fail."
	::= { apSecurityAuthNotifications 4 }

    apSecurityTunnelFailureInetNotification	NOTIFICATION-TYPE
	OBJECTS		{
			apSecuritySpi,
			apSecuritySrcAddressFamily,
			apSecuritySrcAddress,
			apSecurityDstAddressFamily,
			apSecurityDstAddress,
			apSecurityFailureCause,
			apSecurityFailureArea,
			apSecurityStatus
			}
	STATUS	   	current
	DESCRIPTION
	      "The notification will be generated whenever IPSEC IKEV2 tunnel fails to 
	      establish. "
	::= { apSecurityAuthNotifications 5 }

    apSecurityAuthFailureThresholdInetNotification	NOTIFICATION-TYPE
	OBJECTS		{
	                apSecurityUser,
			apSecurityPeerAddressFamily,
			apSecurityPeerAddress,
			apSecurityPeerPort
			}
	STATUS	   	current
	DESCRIPTION
	      "The notification will be generated when IKE DDos auth-failure-threshold is reached and
	      report mode includes SNMP trap"
	::= { apSecurityAuthNotifications 6 }

    apSecurityGeneralNotificationsPrefix
		OBJECT IDENTIFIER ::= { apSecurityNotifications 2 }
    apSecurityGeneralNotifications
		OBJECT IDENTIFIER ::= { apSecurityGeneralNotificationsPrefix 0 }
    apSecurityTunnelDPDNotification	NOTIFICATION-TYPE
	OBJECTS		{
			apSecuritySpi,
			apSecuritySrcIpAddress,
			apSecurityDstIpAddress,
			apSecurityFailureArea,
			apSecurityStatus
			}
	STATUS	   	current
	DESCRIPTION
	      "The notification will be generated whenever IPSEC IKEV2 tunnel fails 
	      due to Dead Peer Detection(DPD). "
	::= { apSecurityGeneralNotifications 1 }

    apSecurityIPsecTunCapNotification	NOTIFICATION-TYPE
	OBJECTS		{
			apSecurityIPsecTunCapPct
			}
	STATUS  current
        DESCRIPTION
		"This notification is sent when the percentage of licensed
		IPsec tunnels exceeds an IPsec tunnel alarm threshold.
		The apSecurityIPsecTunCapPct object indicates the current
		percentage."
        ::= { apSecurityGeneralNotifications 2 }

    apSecurityIPsecTunCapClearNotification    NOTIFICATION-TYPE
	OBJECTS		{
			apSecurityIPsecTunCapPct
			}
	STATUS  current
	DESCRIPTION
		"This trap is sent when the percentage of licensed IPsec
		tunnels no longer exceeds an IPsec tunnel alarm threshold.
		The apSecurityIPsecTunCapPct object indicates the current
		percentage."
	::= { apSecurityGeneralNotifications 3 }


    apSecurityTunnelDPDInetNotification		NOTIFICATION-TYPE
	OBJECTS		{
			apSecuritySpi,
			apSecuritySrcAddressFamily,
			apSecuritySrcAddress, 
			apSecurityDstAddressFamily,
			apSecurityDstAddress, 						
			apSecurityFailureArea,
			apSecurityStatus
			}
	STATUS	   	current
	DESCRIPTION
	      "The notification will be generated whenever IPSEC IKEV2 tunnel fails 
	      due to Dead Peer Detection(DPD). "
	::= { apSecurityGeneralNotifications 4 }

    apSecurityOCSRNotificationsPrefix
		OBJECT IDENTIFIER ::= { apSecurityNotifications 3 }
    apSecurityOCSRNotifications
		OBJECT IDENTIFIER ::= { apSecurityOCSRNotificationsPrefix 0 }

    apSecurityOCSRDownNotification	NOTIFICATION-TYPE
	OBJECTS		{
			apSecurityOCSRHostname,
                        apSecurityOCSRIpAddress
			}
	STATUS  current
        DESCRIPTION
		"This notification is sent when a OCSR server
		becomes unreachable."
        ::= { apSecurityOCSRNotifications 1 }

    apSecurityOCSRUpNotification    NOTIFICATION-TYPE
	OBJECTS		{
			apSecurityOCSRHostname,
                        apSecurityOCSRIpAddress
			}
	STATUS  current
	DESCRIPTION
		"This notification is sent when a OCSR server
		becomes reachable."
	::= { apSecurityOCSRNotifications 2 }

    apSecurityCrlNotificationsPrefix
		OBJECT IDENTIFIER ::= { apSecurityNotifications 4 }
    apSecurityCrlNotifications
		OBJECT IDENTIFIER ::= { apSecurityCrlNotificationsPrefix 0 }

    apSecurityCrlInvalidNotification	NOTIFICATION-TYPE
	OBJECTS		{
			apSecurityCrlIssuer,
                        apSecurityCspName
			}
	STATUS  current
        DESCRIPTION
		"This notification is sent when an invalid CRL
		is detected."
        ::= { apSecurityCrlNotifications 1 }


    apSecurityCRLRetrievalNotificationsPrefix
		OBJECT IDENTIFIER ::= { apSecurityNotifications 5 }
    apSecurityCRLRetrievalNotifications
		OBJECT IDENTIFIER ::= { apSecurityCRLRetrievalNotificationsPrefix 0 }

    apSecurityCRLRetrievalFailNotification	NOTIFICATION-TYPE
	OBJECTS		{
			apSecurityCRLServer,
			apSecurityCRLRetrievalFailureCause,
			apSecurityLastSuccessfulCRLRetrieval,
			apSecurityCRLServerIPAddress
			}
	STATUS  current
        DESCRIPTION
		"This notification is sent when there is a 
		failure in CRL retrieval."		
        ::= { apSecurityCRLRetrievalNotifications 1 }

    apSecurityCRLRetrievalClearNotification    NOTIFICATION-TYPE
	OBJECTS		{
			apSecurityCRLServer,
			apSecurityCRLServerIPAddress
			}
	STATUS  current
	DESCRIPTION
		"This notification is sent when there is a 
		success in CRL retrieval."
	::= { apSecurityCRLRetrievalNotifications 2 }

-- certificate expiration notifications
    apSecurityCertNotificationsPrefix
		OBJECT IDENTIFIER ::= { apSecurityNotifications 6 }
    apSecurityCertNotifications
		OBJECT IDENTIFIER ::= { apSecurityCertNotificationsPrefix 0 }

    apSecurityCertExpiredNotification	NOTIFICATION-TYPE
	OBJECTS		{
	                apSecurityCertificateRecordName,
	                apSecurityCertificateCertSubject,
	                apSecurityCertificateCertExpire,
                        apSecurityCertificateCertIssuer
			}
	STATUS	   	current
	DESCRIPTION
	      "The notification will be generated periodically if a locally installed
               certificate has expired. "
	::= { apSecurityCertNotifications 1 }

    apSecurityCertExpireSoonNotification	NOTIFICATION-TYPE
	OBJECTS		{
                        apSecurityCertificateRecordName,
	                apSecurityCertificateCertSubject,
	                apSecurityCertificateCertExpire,
                        apSecurityCertificateCertIssuer
			}
	STATUS	   	current
	DESCRIPTION
	      "The notification will be generated periodically if a locally installed
               certificate will soon expire. "
	::= { apSecurityCertNotifications 2 }


    apSecurityGTPFailureNotificationsPrefix
             OBJECT IDENTIFIER ::= { apSecurityNotifications 7 }
    apSecurityGTPFailureNotifications
             OBJECT IDENTIFIER ::= { apSecurityGTPFailureNotificationsPrefix 0 }

    apSecurityGTPLinkFailureNotification      NOTIFICATION-TYPE
        OBJECTS         {
                        apSecurityGTPProfileName,
                        apSecurityGTPHostName,
                        apSecurityGTPLinkFailureCause,
                        apSecurityGTPIPAddress
                        }
        STATUS  current
        DESCRIPTION
                "This notification is sent when there is a link failure with GGSN/PGW on GTP Profile."
        ::= { apSecurityGTPFailureNotifications 1 }

    apSecurityGTPLinkClearNotification    NOTIFICATION-TYPE
        OBJECTS         {
                        apSecurityGTPProfileName,
                        apSecurityGTPHostName,
                        apSecurityGTPIPAddress
                        }
        STATUS  current
        DESCRIPTION
                "This notification is sent when the link is restored with GGSN/PGW on GTP Profile."
        ::= { apSecurityGTPFailureNotifications 2 }


    apSecurityTacacsNotificationsPrefix
		OBJECT IDENTIFIER ::= { apSecurityNotifications 9 }
    apSecurityTacacsNotifications
		OBJECT IDENTIFIER ::= { apSecurityTacacsNotificationsPrefix 0 }

    apSecurityTacacsDownLocalAuthUsedTrap	NOTIFICATION-TYPE
        OBJECTS   	{ apSecurityTacacsDownLocalAuthUsed }
        STATUS	   	current
        DESCRIPTION
            "The trap will be generated when a user remotely logs into a system configured for 
            TACACS+ authentication and is authenticated locally by the system because all of 
            the configured and enabled TACACS+ servers have become unreachable or unresponsive." 
        ::= { apSecurityTacacsNotifications 1 }

    apSecurityTacacsDownLocalAuthUsedClearTrap	NOTIFICATION-TYPE
        STATUS	   	current
        DESCRIPTION
            "The trap will be generated when a user remotely logs into a system configured for 
            TACACS+ authentication and is successfully authenticated (i.e., access accepted or 
            denied) remotely by a configured and enabled TACACS+ server."
        ::= { apSecurityTacacsNotifications 2 }
   
--- TLS notifications

    apSecurityTlsNotificationsPrefix
		OBJECT IDENTIFIER ::= { apSecurityNotifications 10 }
    apSecurityTlsNotifications
		OBJECT IDENTIFIER ::= { apSecurityTlsNotificationsPrefix 0 }

    apSecurityTlsEncryptionFailureNotification	NOTIFICATION-TYPE
	OBJECTS		{
			apSecuritySrcAddressFamily,
			apSecuritySrcAddress,
			apSecuritySrcPort,
			apSecurityDstAddressFamily,
			apSecurityDstAddress,
			apSecurityDstPort,
			apSecurityTlsEncryptionFailureCause,
			apSecurityTlsCipherSuite,
			apSecurityTlsSessionId,
			apSecurityTlsPacketFailureCount
			}
	STATUS	   	current
	DESCRIPTION
	      "The notification will be generated when TLS fails to 
	      encrypt."
	::= { apSecurityTlsNotifications 1 }

    apSecurityTlsDecryptionFailureNotification	NOTIFICATION-TYPE
	OBJECTS		{
			apSecuritySrcAddressFamily,
			apSecuritySrcAddress,
			apSecuritySrcPort,
			apSecurityDstAddressFamily,
			apSecurityDstAddress,
			apSecurityDstPort,
			apSecurityTlsDecryptionFailureCause,
			apSecurityTlsCipherSuite,
			apSecurityTlsSessionId,
			apSecurityTlsPacketFailureCount
			}
	STATUS	   	current
	DESCRIPTION
	      "The notification will be generated when TLS fails to 
	      decrypt."
	::= { apSecurityTlsNotifications 2 }

--- SRTP notifications

    apSecuritySrtpNotificationsPrefix
		OBJECT IDENTIFIER ::= { apSecurityNotifications 11 }
    apSecuritySrtpNotifications
		OBJECT IDENTIFIER ::= { apSecuritySrtpNotificationsPrefix 0 }
    
    apSecuritySrtpEncryptionFailureNotification	NOTIFICATION-TYPE
	OBJECTS		{
			apSecuritySrcAddressFamily,
			apSecuritySrcAddress,
			apSecuritySrcPort,
			apSecurityDstAddressFamily,
			apSecurityDstAddress,
			apSecurityDstPort,
			apSecuritySrtpEncryptionFailureCause,
			apSecuritySrtpEncrAlgorithm,
			apSecuritySrtpAuthAlgorithm
			}
	STATUS	   	current
	DESCRIPTION
	      "The notification will be generated when SRTP fails to 
	      encrypt."
	::= { apSecuritySrtpNotifications 1 }

    apSecuritySrtpDecryptionFailureNotification	NOTIFICATION-TYPE
	OBJECTS		{
			apSecuritySrcAddressFamily,
			apSecuritySrcAddress,
			apSecuritySrcPort,
			apSecurityDstAddressFamily,
			apSecurityDstAddress,
			apSecurityDstPort,
			apSecuritySrtpDecryptionFailureCause,
			apSecuritySrtpEncrAlgorithm,
			apSecuritySrtpAuthAlgorithm
			}
	STATUS	   	current
	DESCRIPTION
	      "The notification will be generated when SRTP fails to 
	      decrypt."
	::= { apSecuritySrtpNotifications 2 }

    -- Conformance information

apSecurityConformance OBJECT IDENTIFIER ::= { apSecurityModule 4 }
apSecurityCompliances OBJECT IDENTIFIER ::= { apSecurityConformance 1 }
apSecurityGroups   OBJECT IDENTIFIER ::= { apSecurityConformance 2 }
apSecurityNotificationsGroups
		     OBJECT IDENTIFIER ::= { apSecurityConformance 3 }
------objects group

apSecurityIPsecTunnelsObjectsGroup OBJECT-GROUP
	OBJECTS {
		apSecurityIPsecTunCount,
		apSecurityIPsecTunCapPct
		}
	STATUS	current
	DESCRIPTION
		"Objects for monitoring IPsec tunnel capacity."
	::= { apSecurityGroups 1 }

apSecurityIkeInterfaceObjectsGroup OBJECT-GROUP
	OBJECTS {
            apSecurityIkeInterfaceInitCookieErrors,
            apSecurityIkeInterfaceAuthErrors,
            apSecurityIkeInterfaceEapAccessRequestErrors,
            apSecurityIkeInterfaceEapAccessChallengeErrors,
            apSecurityIkeInterfaceTsErrors,
            apSecurityIkeInterfaceCpErrors,
            apSecurityIkeInterfaceKeErrors,
            apSecurityIkeInterfaceProposalErrors,
            apSecurityIkeInterfaceSyntaxErrors,
            apSecurityIkeInterfaceCriticalPayloadErrors,
            apSecurityIkeInterfaceEapOnlyNonZeroSPI,
            apSecurityIkeInterfaceEapOnlyNonZeroProtoId,
            apSecurityIkeInterfaceEapOnlyUnSupEapProto
		}
	STATUS	current
	DESCRIPTION
		"Objects for monitoring IKE negotiation errors."
	::= { apSecurityGroups 2 }

apSecurityTacacsObjectsGroup OBJECT-GROUP
	OBJECTS {
                apSecurityTacacsServer,
                apSecurityTacacsCliCommands,
                apSecurityTacacsSuccessAuthentication,
                apSecurityTacacsFailureAuthentication,
                apSecurityTacacsSuccessAuthorization,
                apSecurityTacacsFailureAuthorization
		}
	STATUS	current
	DESCRIPTION
		"Objects for monitoring TACACS+ transactions."
	::= { apSecurityGroups 3 }
				 
apSecurityCertObjectsGroup OBJECT-GROUP
        OBJECTS {
		apSecurityCertificateRecordName,
                apSecurityCertificateCertSubject,
		apSecurityCertificateCertStart,
		apSecurityCertificateCertExpire,
                apSecurityCertificateCertIssuer,
		apSecurityCertificateCertIsCA
                }
       STATUS   current
       DESCRIPTION
	        "Objects for managing locally installed certificates. "
       ::= { apSecurityGroups 4 }
       
apSecurityIkeInterfaceInfoObjectsGroup OBJECT-GROUP
	OBJECTS {
                apSecurityIkeInterfaceTunnelRate,
                apSecurityIkeInterfaceCurrentChildSaPair,
                apSecurityIkeInterfaceTunnelTearDownRate
		}
	STATUS	current
	DESCRIPTION
		"Objects for monitoring IKE interface tunnel information"
	::= { apSecurityGroups 5 }

apSecurityIkeIfcBlAuthIDErrorObjectsGroup OBJECT-GROUP
	OBJECTS {
                apSecurityIkeInterfaceBlacklistAuthIDError
		}
	STATUS	current
	DESCRIPTION
		"Objects for monitoring IKE interface Blacklist AuthID error information"
	::= { apSecurityGroups 6 }

apSecurityDhcpInterfaceObjectsGroup OBJECT-GROUP
	OBJECTS {
		apSecurityDhcpInterfaceType,
		apSecurityDhcpInterfaceAddress,
		apSecurityDhcpInterfaceDisRcvd,
		apSecurityDhcpInterfaceOfferSent,
		apSecurityDhcpInterfaceReqRcvd,
		apSecurityDhcpInterfaceAckSent,
		apSecurityDhcpInterfaceNAckSent,
		apSecurityDhcpInterfaceRelRcvd,
		apSecurityDhcpInterfaceFailures,
		apSecurityDhcpInterfaceRelRcvd,
		apSecurityDhcpInterfaceOfferTimeouts,
		apSecurityDhcpInterfaceLeaseTimeouts,
		apSecurityDhcpInterfaceCurrentSessions,
		apSecurityDhcpInterfaceMaxSessions,
		apSecurityDhcpInterfaceTotalSessions  
		}
	STATUS	current
	DESCRIPTION
		"Objects for monitoring DHCP interface negotiations"
	::= { apSecurityGroups 7 }			

apSecurityGtpProfileObjectsGroup OBJECT-GROUP
        OBJECTS {
                apSecurityGtpProfile,
		apSecurityGtpAddressType,
                apSecurityGtpAddress,
                apSecurityGtpHost,
                apSecurityGtpTunnelsCreated,
                apSecurityGtpCPDPReqSent,
                apSecurityGtpCPDPReqRcvd,
                apSecurityGtpCPDPSuccRespSent,
                apSecurityGtpCPDPSuccRespRcvd,
                apSecurityGtpCPDPFailRespSent,
                apSecurityGtpCPDPFailRespRcvd,
                apSecurityGtpCPDPIncompleteRespRcvd,
                apSecurityGtpCPDPRespCtxtNotFound,
                apSecurityGtpCPDPFailInternalError,
                apSecurityGtpCPDPRespTimeout,
                apSecurityGtpUPDPReqSent,
                apSecurityGtpUPDPReqRcvd,
                apSecurityGtpUPDPSuccRespSent,
                apSecurityGtpUPDPSuccRespRcvd,
                apSecurityGtpUPDPFailRespSent,
                apSecurityGtpUPDPFailRespRcvd,
                apSecurityGtpUPDPRespTimeout, 
                apSecurityGtpDPDPReqSent,
                apSecurityGtpDPDPReqRcvd,
                apSecurityGtpDPDPSuccRespSent,
                apSecurityGtpDPDPSuccRespRcvd,
                apSecurityGtpDPDPFailRespSent,
                apSecurityGtpDPDPFailRespRcvd,
                apSecurityGtpDPDPRespTimeout,
                apSecurityGtpVersionNotSuppSent,
                apSecurityGtpVersionNotSuppRcvd,
                apSecurityGTPCEchoReqSent,
                apSecurityGTPCEchoReqRcvd,
                apSecurityGTPCEchoRespSent,
                apSecurityGTPCEchoRespRcvd,
                apSecurityGTPCEchoRespTimeout,
                apSecurityGTPUEchoReqSent,
                apSecurityGTPUEchoReqRcvd,
                apSecurityGTPUEchoRespSent,
                apSecurityGTPUEchoRespRcvd,
                apSecurityGTPUEchoRespTimeout,
		apSecurityGtpV2CreateSesssionReqSent,    
                apSecurityGtpV2CreateSesssionReqSentFail,
                apSecurityGtpV2CreateSessionRespRcvd,    
                apSecurityGtpV2CreateSessionRespFailRcvd,
                apSecurityGtpV2CreateSessionRespTimeout, 
                apSecurityGtpV2DeleteSessionReqSent,     
                apSecurityGtpV2DeleteSessionReqSentFail, 
                apSecurityGtpV2DeleteSessionRespRcvd,    
                apSecurityGtpV2DeleteSessionRespRcvdFail,
                apSecurityGtpV2DeleteSessionRespTimeout,
                apSecurityGtpV2DeleteBearerReqRcvd,      
                apSecurityGtpV2DeleteBearerReqRcvdFail,  
                apSecurityGtpV2DeleteBearerRespSent,     
                apSecurityGtpV2DeleteBearerRespSentFail, 
                apSecurityGtpV2CreateBearerReqRcvd,      
                apSecurityGtpV2CreateBearerReqRcvdFail,  
                apSecurityGtpV2CreateBearerRespSent,     
                apSecurityGtpV2CreateBearerRespSentFail, 
                apSecurityGtpV2UpdateBearerReqRcvd,      
                apSecurityGtpV2UpdateBearerReqRcvdFail,  
                apSecurityGtpV2UpdateBearerRespSent,     
                apSecurityGtpV2UpdateBearerRespSentFail, 
                apSecurityGTPErrorIndRcvd
        }
	STATUS	current
	DESCRIPTION
		"Objects for monitoring Gtp profile negotiations"
	::= { apSecurityGroups 8 }			

apSecurityGtpErrorObjectsGroup OBJECT-GROUP
        OBJECTS {
                apSecurityGtpMsgDiffVer,
                apSecurityGtpInvalidMsgLen,
                apSecurityGtpUnknownMsg,
                apSecurityGtpUnexpectedMsg,
                apSecurityGtpMissingMandIE,
                apSecurityGtpMissingReqIE,
		apSecurityGtpMissingContIE,
                apSecurityGtpInvalidIELen,
                apSecurityGtpInvalidMandIE,
                apSecurityGtpInvalidOptIE,
                apSecurityGtpUnknownIE,
                apSecurityGtpInvalidSeqIE,
                apSecurityGtpUnexpectedIE,
                apSecurityGtpRepeatedIE,
                apSecurityGtpIncorrectOptIE,
                apSecurityGtpTunnelNonExistent,
                apSecurityGtpInvalidMsgFormat,
                apSecurityGtpErrorIndCtxtNotFound,
		        apSecurityGtpInvalidPCOFormat,	
                apSecurityGtpSemanticTFTError,
                apSecurityGtpSyntacticTFTError,
                apSecurityGtpSemanticPFError,
                apSecurityGtpSyntacticPFError,
		        apSecurityGtpInvalidAPCOFormat	
        }
	STATUS	current
	DESCRIPTION
		"Objects for monitoring Gtp protocol errors"
	::= { apSecurityGroups 9 }			

apSecurityRekeyOnSNoverflowObjectsGroup OBJECT-GROUP
	OBJECTS {
                apSecurityIkeInterfaceRekeyOnSNoverflow
		}
	STATUS	current
	DESCRIPTION
		"Objects for monitoring number of rekeys occurred due to SN overflows"
	::= { apSecurityGroups 10 }
    
apSecurityIkeInterfaceDpdStatsObjectsGroup OBJECT-GROUP
	OBJECTS {
            apSecurityIkeInterfaceDPDRecvPortChange,
            apSecurityIkeInterfaceDPDRecvIPChange,
            apSecurityIkeInterfaceDPDRespRecv,
            apSecurityIkeInterfaceDPDRespNotRecv,
            apSecurityIkeInterfaceDPDRecv,
            apSecurityIkeInterfaceDPDRetran,
            apSecurityIkeInterfaceDPDSent,
            apSecurityIkeInterfaceDPDFailSaDel
		}
	STATUS	current
	DESCRIPTION
		"Objects for monitoring IKE Interface DPD statistics."
	::= { apSecurityGroups 11 }

apSecurityIkeInterfaceEapOnlyAuthStatsGroup OBJECT-GROUP
	OBJECTS {
            apSecurityIkeInterfaceEapOnlyAuthentication, 
            apSecurityIkeInterfaceEapOnlyWithAuthPayload,
            apSecurityIkeInterfaceEapOnlyNonZeroSPI,
            apSecurityIkeInterfaceEapOnlyNonZeroProtoId,
            apSecurityIkeInterfaceEapOnlyUnSupEapProto
		}
	STATUS	current
	DESCRIPTION
		"Objects for monitoring EAP_ONLY Auth related statistics."
	::= { apSecurityGroups 12 }

apSecurityIkeInterfaceMobikeStatsGroup OBJECT-GROUP
	OBJECTS {
            apSecurityIkeInterfaceMobikeSupportRequest,
            apSecurityIkeInterfaceMobikeSupportResponse,      
            apSecurityIkeInterfaceMobikeUpdateSAAddrRcvd,       
            apSecurityIkeInterfaceMobikeUpdateSASuccess,         
            apSecurityIkeInterfaceMobikeUpdateSAAddrFamMismatch,
            apSecurityIkeInterfaceMobikeUpdateSAFailUnexpUpdate, 
            apSecurityIkeInterfaceMobikeUpdateSASameAddress,
            apSecurityIkeInterfaceMobikeUpdateSAFailInternal,
            apSecurityIkeInterfaceMobikeReturnRouteCheckRequests,
            apSecurityIkeInterfaceMobikeFailToSendRouteCheck,
            apSecurityIkeInterfaceMobikeReturnRouteCheckSuccess, 
            apSecurityIkeInterfaceMobikeReturnRouteCheckTimeout,
            apSecurityIkeInterfaceMobikeRouteCheckFailSAdel,
            apSecurityIkeInterfaceMobikeIntSaCommFailSaDel,
            apSecurityIkeInterfaceMobikeMisMatchCookie2Errors
		}
	STATUS	current
	DESCRIPTION
		"Objects for monitoring Mobike related statistics."
	::= { apSecurityGroups 17 }

-- notification groups

apSecurityNotificationsGroup NOTIFICATION-GROUP
	NOTIFICATIONS  {
		apSecurityTunnelFailureNotification,
		apSecurityRadiusFailureNotification,
		apSecurityTunnelDPDNotification,
                apSecurityTacacsFailureNotification
		}
	STATUS   current
        DESCRIPTION
                 "A collection of notifications for security "
	::= {  apSecurityNotificationsGroups 1 }

apSecurityIPsecTunnelsNotificationsGroup NOTIFICATION-GROUP
	NOTIFICATIONS  {
		apSecurityIPsecTunCapNotification,
		apSecurityIPsecTunCapClearNotification
		}
	STATUS   current
        DESCRIPTION
                 "A collection of notifications for IPsec tunnel capacity."
	::= {  apSecurityNotificationsGroups 2 }

apSecurityDDosNotificationsGroup NOTIFICATION-GROUP
	NOTIFICATIONS  {
		apSecurityAuthFailureThresholdNotification
		}
	STATUS   current
        DESCRIPTION
                 "A collection of notifications for IKEv2 DDos "
	::= {  apSecurityNotificationsGroups 3 }

apSecurityOCSRNotificationsGroup NOTIFICATION-GROUP
	NOTIFICATIONS  {
		apSecurityOCSRDownNotification,
		apSecurityOCSRUpNotification
		}
	STATUS   current
        DESCRIPTION
                 "A collection of notifications for OCSRs "
	::= {  apSecurityNotificationsGroups 4 }

apSecurityCrlNotificationsGroup NOTIFICATION-GROUP
	NOTIFICATIONS  {
		apSecurityCrlInvalidNotification
		}
	STATUS   current
        DESCRIPTION
                 "A collection of notifications for CRLs "
	::= {  apSecurityNotificationsGroups 5 }


apSecurityCRLRetrievalNotificationsGroup NOTIFICATION-GROUP
	NOTIFICATIONS  {
		apSecurityCRLRetrievalFailNotification,
		apSecurityCRLRetrievalClearNotification
		}
	STATUS   current
        DESCRIPTION
                 "A collection of notifications for CRL Retrieval "
	::= {  apSecurityNotificationsGroups 6 }


apSecurityCertNotificationsGroup NOTIFICATION-GROUP
	NOTIFICATIONS  {
                apSecurityCertExpiredNotification,
                apSecurityCertExpireSoonNotification
		}
	STATUS   current
        DESCRIPTION
                 "A collection of notifications for CRLs "
	::= {  apSecurityNotificationsGroups 7 }

apSecurityGTPNotificationsGroup NOTIFICATION-GROUP
        NOTIFICATIONS  {
                apSecurityGTPLinkFailureNotification,
                apSecurityGTPLinkClearNotification
                }
        STATUS   current
        DESCRIPTION
                 "A collection of notifications for GTP peer communication "
        ::= {  apSecurityNotificationsGroups 8 }

apSecurityNotificationsInetGroup NOTIFICATION-GROUP
	NOTIFICATIONS  {
		apSecurityTunnelFailureInetNotification,			
		apSecurityRadiusFailureNotification,
		apSecurityTunnelDPDInetNotification,
                apSecurityTacacsFailureNotification
		}
	STATUS   current
        DESCRIPTION
                 "A collection of notifications for security "
	::= {  apSecurityNotificationsGroups 9 }

apSecurityDDosNotificationsInetGroup NOTIFICATION-GROUP
	NOTIFICATIONS  {
		apSecurityAuthFailureThresholdInetNotification
		}
	STATUS   current
        DESCRIPTION
                 "A collection of notifications for IKEv2 DDos "
	::= {  apSecurityNotificationsGroups 10 }

apSecurityTacacsDownLocalAuthTrapGroup NOTIFICATION-GROUP
	NOTIFICATIONS  {
        apSecurityTacacsDownLocalAuthUsedTrap,
        apSecurityTacacsDownLocalAuthUsedClearTrap
		}
	STATUS   current
        DESCRIPTION
            "A collection of traps for monitoring TACACS+ authentication service 
            unavailability resulting in the system falling back to use local 
            user accounts to authenticate the user."
        ::= { apSecurityNotificationsGroups 12 }

apSecurityTlsNotificationsGroup NOTIFICATION-GROUP
	NOTIFICATIONS  {
		apSecurityTlsEncryptionFailureNotification,
		apSecurityTlsEncryptionFailureNotification
		}
	STATUS   current
        DESCRIPTION
                 "A collection of notifications for TLS encryption/decryption failures."
	::= {  apSecurityNotificationsGroups 13 }

apSecuritySrtpNotificationsGroup NOTIFICATION-GROUP
	NOTIFICATIONS  {
		apSecuritySrtpEncryptionFailureNotification,
		apSecuritySrtpDecryptionFailureNotification
		}
	STATUS   current
        DESCRIPTION
                 "A collection of notifications for SRTP encryption/decryption failures."
	::= {  apSecurityNotificationsGroups 14 }
	

--	
-- TSCF STATISTICS

apSecurityTscfStatsGroup  OBJECT-GROUP
        OBJECTS {
                 apTscfActiveTunnels,
                 apTscfEstablishedTunnels,
                 apTscfFinishedTunnels,
                 apTscfReleasedTunnels,
                 apTscfMaxActiveTunnels,
                 apTscfConfReqReceived,
                 apTscfConfReqNagleReceived,
                 apTscfConfRespSent,
                 apTscfConfRelReqReceived,
                 apTscfConfRelRespSent,   
                 apTscfCSResponseSent,
                 apTscfCSREnableDDT,
                 apTscfCSRDisableDDT,
                 apTscfCSREnableRedundancy,
                 apTscfCSRDisableRedundancy,
                 apTscfKAReceived,
                 apTscfKARespSent,
                 apTscfKASent,
                 apTscfKARespRcvd,
                 apTscfCMReTx,          
                 apTscfFailureMalformed,
                 apTscfFailureUnkownMsg,
                 apTscfFailureClientAssignedIP,
                 apTscfFailureCannotProvisionIP,
                 apTscfFailureAlreadyProvisionedIP,
                 apTscfFailureGeneralProvisionIP,
                 apTscfFailureClientAssignedIPMask,
                 apTscfFailureCannotProvisionIPMask,
                 apTscfFailureAlreadyProvisionedIPMask,
                 apTscfFailureGeneralProvisionIPMask,   
                 apTscfFailureClientAssignedSIPServer,
                 apTscfFailureCannotProvisionSIPServer,
                 apTscfFailureAlreadyProvisionedSIPServer,
                 apTscfFailureGeneralProvisionSIPServer,
                 apTscfFailureClientAsignedKA,
                 apTscfFailureCannotProvisionKA,
                 apTscfFailureAlreadyProvisionedKA,
                 apTscfFailureGeneralProvisionKA,
                 apTscfFailureNonExistentTunnelId,
                 apTscfFailureOutOfResources,   
                 apTscfFailureInternalIPExhausted,
                 apTscfFailureNonNullIPAddr,
                 apTscfFailureNonNullIpMask,
                 apTscfFailureNonNullSipServer,
                 apTscfFailureNonNullKeepAlive,
                 apTscfFailureNoListeningFd,
                 apTscfFailureServerFailure,
                 apTscfFailureRedundancyNotEnabled,
                 apTscfFailureRedundancyExceedsLimit,
                 apTscfFailureTunnelIdExhausted,   
                 apTscfFailureTimerFailure,
                 apTscfFailureDDTNotEnabled,
                 apTscfFailureDDTWrongTransport,
                 apTscfFailureDDTDatagramOnly,
                 apTscfFailureDDTInconsistantTransport,
                 apTscfFailureUnkownServiceRequest,
                 apTscfFailureTunnelEstablished,
                 apTscfFailureAddrPoolUnavilable,
                 apTscfFailureListenFdUnavailable,
                 apTscfFailureVersionNotSupported, 
                 apTscfFailureLicenseExceeded,
                 apTscfFailureNoTunnelForPkt,
                 apTscfWrongSeqNum,
                 apTscfConDrop,
                 apTscfIntfConDrop,
                 apTscfStatsAllocs,
                 apTscfStatsFrees,
                 apTscfStatsMemFails,
                 apTscfSwitchToActive,
                 apTscfSwitchToStandBy, 
                 apTscfGetDTLSCtxSent,
                 apTscfGetDTLSCtxSuccess,
                 apTscfGetDTLSCtxFailed,
                 apTscfSetDTLSCtxSent,
                 apTscfSetDTLSCtxSuccess,
                 apTscfSetDTLSCtxFailed,
                 apTscfFdTableSize,
                 apTscfAddressTableSize,
                 apTscfTunnelTableSize,
                 apTscfActiveTunnelTableSize,   
                 apTscfFlowIdTableSize,
                 apTscfLicenseTunnelCount,
                 apTscfSpecificAddressCount,
                 apTscfTunnelTimeoutCount,
                 apTscfTunneledPacketDrop,
                 apTscfUnTunneledPacketDrop,
                 apTscfCsrReceived,
                 apTscfTypeInnerIPDestDrop
                }
        STATUS  current
        DESCRIPTION
                "Objects for TSCF statistics."
        ::= { apSecurityGroups 13 }


apSecurityIkeInterfaceEapMethodsStatsGroup OBJECT-GROUP
	OBJECTS {
                apSecurityIkeInterfaceEapSimSucc,
                apSecurityIkeInterfaceEapSimFail,
                apSecurityIkeInterfaceEapAkaSucc,
                apSecurityIkeInterfaceEapAkaFail,
                apSecurityIkeInterfaceEapAkaPrimeSucc,
                apSecurityIkeInterfaceEapAkaPrimeFail,
                apSecurityIkeInterfaceEapTlsSucc,
                apSecurityIkeInterfaceEapTlsFail,
                apSecurityIkeInterfaceEapTtlsSucc,
                apSecurityIkeInterfaceEapTtlsFail,
                apSecurityIkeInterfaceEapOtherSucc,
                apSecurityIkeInterfaceEapOtherFail 
		}
	STATUS	current
	DESCRIPTION
		"Objects for monitoring eap method related  auth statistics."
	::= { apSecurityGroups 14 }

apSecurityIkeInterfaceIkeStatsGroup OBJECT-GROUP
	OBJECTS {
            apSecurityIkeInterfaceNatKeepAliveMsgsRecv,
            apSecurityIkeInterfaceBroadcastOrMulticastMsgcRecv,
            apSecurityIkeInterfaceIkeSaAuthMsgsRecv,
            apSecurityIkeInterfaceIkeSaAuthMsgsSent,
            apSecurityIkeInterfaceIkeSaChildMsgsRecv,
            apSecurityIkeInterfaceIkeSaChildMsgsSent,
            apSecurityIkeInterfaceIkeSaInfoMsgsRecv,
            apSecurityIkeInterfaceIkeSaInfoMsgsSent,
            apSecurityIkeInterfaceInIkeSaRekeyRequest,
            apSecurityIkeInterfaceInIkeSaRekeyRequestSuccess,
            apSecurityIkeInterfaceInIkeSaRekeyRequestFailure,
            apSecurityIkeInterfaceOutIkeSaRekeyRequest,
            apSecurityIkeInterfaceOutIkeSaRekeyRequestSuccess,
            apSecurityIkeInterfaceOutIkeSaRekeyRequestFailure,
            apSecurityIkeInterfaceInIkeSaDeleteRequest,
            apSecurityIkeInterfaceInIkeSaDeleteRequestSuccess,
            apSecurityIkeInterfaceInIkeSaDeleteRequestFailure,
            apSecurityIkeInterfaceOutIkeSaDeleteRequest,
            apSecurityIkeInterfaceHalfOpenSecurityAssociations,
            apSecurityIkeInterfaceIkeTunnelAvgHoldTime,
            apSecurityIkeInterfaceIkeTunnelAvgSetupTime
		}
	STATUS	current
	DESCRIPTION
		"Objects for monitoring ike related statistics."
	::= { apSecurityGroups 15 }

apSecurityIkeInterfaceIkeErrorsGroup OBJECT-GROUP
	OBJECTS {
            apSecurityIkeInterfaceIkeBadPortErrors,
            apSecurityIkeInterfaceIkeBadAttrErrors,
            apSecurityIkeInterfaceIkeBadCertErrors,
            apSecurityIkeInterfaceIkeNoCertErrors,
            apSecurityIkeInterfaceIkeBadCertTypeErrors,
            apSecurityIkeInterfaceIkeBadCookieErrors,
            apSecurityIkeInterfaceIkeBadCookie2Errors,
            apSecurityIkeInterfaceIkeBadConfigErrors,
            apSecurityIkeInterfaceIkeBadHashErrors,
            apSecurityIkeInterfaceIkeBadIDErrors,
            apSecurityIkeInterfaceIkeBadID2Errors,
            apSecurityIkeInterfaceIkeBadKeErrors,
            apSecurityIkeInterfaceIkeBadLenErrors,
            apSecurityIkeInterfaceIkeBadMsgErrors,
            apSecurityIkeInterfaceIkeBadMsgIdErrors,
            apSecurityIkeInterfaceIkeBadNATDErrors,
            apSecurityIkeInterfaceIkeBadNonceErrors,
            apSecurityIkeInterfaceIkeBadNotifyCookieErrors,
            apSecurityIkeInterfaceIkeBadPayloadErrors,
            apSecurityIkeInterfaceIkeBadProposalErrors,
            apSecurityIkeInterfaceIkeBadProtocolErrors,
            apSecurityIkeInterfaceIkeBadSaErrors,
            apSecurityIkeInterfaceIkeBadSigErrors,
            apSecurityIkeInterfaceIkeBadSpiErrors,
            apSecurityIkeInterfaceIkeBadVersionErrors,
            apSecurityIkeInterfaceIkeBadXchgErrors,
            apSecurityIkeInterfaceIkeBufferOverflowErrors,
            apSecurityIkeInterfaceIkeConfigErrors,
            apSecurityIkeInterfaceIkeGetSaFailErrors,
            apSecurityIkeInterfaceIkeNewSaFailErrors,
            apSecurityIkeInterfaceIkeNotifyPayloadErrors,
            apSecurityIkeInterfaceIkeNullPSKErrors,
            apSecurityIkeInterfaceIkeMismatchErrors,
            apSecurityIkeInterfaceIkeMismatchAuthAlgoErrors,
            apSecurityIkeInterfaceIkeMismatchAuthMethodErrors,
            apSecurityIkeInterfaceIkeMismatchDHGroupErrors,
            apSecurityIkeInterfaceIkeMismatchEncrAlgoErrors,
            apSecurityIkeInterfaceIkeMismatchKeyLenErrors,
            apSecurityIkeInterfaceCertInvalidStructErrors,
            apSecurityIkeInterfaceCertNotExpectedOIDErrors,
            apSecurityIkeInterfaceCertRsaExponentTooBigErrors,
            apSecurityIkeInterfaceCertExpiredErrors,
            apSecurityIkeInterfaceCertInvalidParentCertificateErrors,
            apSecurityIkeInterfaceCertUnsupportedDigestErrors,
            apSecurityIkeInterfaceCertDNEStringTooLongErrors,
            apSecurityIkeInterfaceCertStackOverflowErrors,
            apSecurityIkeInterfaceCertKeyUsageMissingErrors,
            apSecurityIkeInterfaceCertUnknownCriticalExtensionErrors,
            apSecurityIkeInterfaceCertUnSupportedSignatureAlgoErrors,
            apSecurityIkeInterfaceCertRSAModulusTooBigErrors,
            apSecurityIkeInterfaceEapInstanceIdNotFoundErrors,
            apSecurityIkeInterfaceEapInvalidPktSizeErrors,
            apSecurityIkeInterfaceEapInvalidMethodTypeErrors,
            apSecurityIkeInterfaceEapInvalidCodeErrors,
            apSecurityIkeInterfaceEapInvalidPktErrors,
            apSecurityIkeInterfaceIkeSaCapacityExceedCount,
            apSecurityIkeInterfaceIpsecSaCapacityExceedCount
		}
	STATUS	current
	DESCRIPTION
		"Objects for monitoring ike related errors."
	::= { apSecurityGroups 16 }

apSecurityTscfStatsTimeoutGroup  OBJECT-GROUP
        OBJECTS {
                 apTscfTunnelsTimedOut
                }
        STATUS  current
        DESCRIPTION
                "Objects for TSCF statistics."
        ::= { apSecurityGroups 18 }

apSecurityIkeInterface3GPPAuthErrorsGroup OBJECT-GROUP
        OBJECTS {
                 apSecurityIkeInterfaceAuthUserUnknownErrors,
                 apSecurityIkeInterfaceAuthPlmnNotAllowedErrors,
                 apSecurityIkeInterfaceAuthNon3GppAccessToEpcNotAllowedErrors,
                 apSecurityIkeInterfaceAuthNoApnSubscriptionErrors,
                 apSecurityIkeInterfaceAuthRatTypeNotAllowedErrors,
                 apSecurityIkeInterfaceAuthAuthorizationRejectedErrors,
                 apSecurityIkeInterfaceAuthNetworkFailureErrors

                }
        STATUS  current
        DESCRIPTION
                "Objects for 3gpp Authentication Errors."
        ::= { apSecurityGroups 19 }

apSecurityGtpCaviumStatsGroup OBJECT-GROUP
        OBJECTS {
                 apSecurityGtpV2CreateSessRespPPMAddFail,
                 apSecurityGtpV2DeleteBReqRcvdPPMDelFail,
                 apSecurityGtpV2CreateBReqPPMAddFail,
                 apSecurityGtpV2UpdateBReqPPMUpdateFail,
                 apSecurityGtpV2StandbyDefBrerPPMAddFail,
                 apSecurityGtpV2StandbyDedBrerPPMAddFail,
                 apSecurityGtpV2StandbyDefBrerPPMDelFail,
                 apSecurityGtpV2StandbyDedBrerPPMDelFail
                }
        STATUS  current
        DESCRIPTION
                "Objects for Gtp Cavium Statistics."
        ::= { apSecurityGroups 20 }
        
apSecuritySAIKEStatsGroup  OBJECT-GROUP
        OBJECTS {
                 apSecSAIKEAddReqRcvd,
                 apSecSAIKEAddSuccessRespSent,
                 apSecSAIKEAddFailRespSent,
                 apSecSAIKEDelReqRcvd,
                 apSecSAIKEDelSuccessRespSent,
                 apSecSAIKEDelFailRespSent,
                 apSecSAIKEAcquireReqSent,
                 apSecSAIKEAcquireSuccessRespRcvd,
                 apSecSAIKEAcquireFailRespRcvd,
                 apSecSAIKEAcquireTransactionTimeout,
                 apSecSAIKESaCreated,
                 apSecSAIKESaCreateFailed,
                 apSecSAIKESaDeleted,
                 apSecSAIKESaDeleteFailed
                }
        STATUS          current
        DESCRIPTION
                "A collection of objects providing SA IKE stats"
        ::= { apSecurityGroups 21 }

apSecuritySAIMSAKAStatsGroup  OBJECT-GROUP
        OBJECTS {
                 apSecSAIMSAKAAddReqSent,
                 apSecSAIMSAKAAddReqRcvd,
                 apSecSAIMSAKAAddSuccessRespSent,
                 apSecSAIMSAKAAddSuccessRespRcvd,
                 apSecSAIMSAKAAddFailRespSent,
                 apSecSAIMSAKAAddFailInvalidParamRespSent,
                 apSecSAIMSAKAAddFailRespRcvd,
                 apSecSAIMSAKAAddFailAddrMaskMismatch,
                 apSecSAIMSAKAAddFailProtoParamsInvalid,
                 apSecSAIMSAKAAddFailProtoDataInvalid,
                 apSecSAIMSAKAAddTransactionTimeout,
                 apSecSAIMSAKADelReqSent,
                 apSecSAIMSAKADelReqRcvd,
                 apSecSAIMSAKADelSuccessRespSent,
                 apSecSAIMSAKADelSuccessRespRcvd,
                 apSecSAIMSAKADelFailRespSent,
                 apSecSAIMSAKADelFailInvalidParamRespSent,
                 apSecSAIMSAKADelFailRespRcvd,
                 apSecSAIMSAKADelTransactionTimeout,    
                 apSecSAIMSAKADelDueToTimeout,        
                 apSecSAIMSAKAModReqSent,
                 apSecSAIMSAKAModReqRcvd,
                 apSecSAIMSAKAModSuccessRespSent,
                 apSecSAIMSAKAModSuccessRespRcvd,
                 apSecSAIMSAKAModFailRespSent,
                 apSecSAIMSAKAModFailInvalidParamRespSent,
                 apSecSAIMSAKAModFailRespRcvd,
                 apSecSAIMSAKAModTransactionTimeout,
                 apSecSAIMSAKASaCreated,
                 apSecSAIMSAKASaCreatedInboundSent,
                 apSecSAIMSAKASaCreatedOutboundSent,
                 apSecSAIMSAKASaCreateFailed,
                 apSecSAIMSAKASaCreatePPMInboundFailed,
                 apSecSAIMSAKASaCreatePPMOutboundFailed,
                 apSecSAIMSAKASaDeleted,
                 apSecSAIMSAKASaDeletedInboundSent,
                 apSecSAIMSAKASaDeletedOutboundSent,
                 apSecSAIMSAKASaDelFailed, 
                 apSecSAIMSAKASaDelPPMInboundFailed,
                 apSecSAIMSAKASaDelPPMOutboundFailed,
                 apSecSAIMSAKASaDelFailAddrMaskMismatch,  
                 apSecSAIMSAKASaDelFailProtoParamsInvalid,
                 apSecSAIMSAKASaDelFailProtoDataInvalid,
                 apSecSAIMSAKASaCollision,      
                 apSecSAIMSAKASaCollisionRecoveryFail,    
                 apSecSAIMSAKASaCollisionRecoverySuccess,
                 apSecSAIMSAKASaCollisionRecoveryLkupFail,     
                 apSecSAIMSAKASaKeyNotFound,
                 apSecSAIMSAKASaKeyNotFoundTimeout,
                 apSecSAIMSAKASaKeyExists,
                 apSecSAIMSAKASaRecovery,    
                 apSecSAIMSAKASaRecoveryFail,
                 apSecSAIMSAKASaTransactionQueue,
                 apSecSAIMSAKASaRedundancySyncQueue,
                 apSecSAIMSAKASaInboundOnly,
                 apSecSAIMSAKASaOutboundOnly,
                 apSecSAIMSAKAAddFailInvalidTimer,
                 apSecSAIMSAKAAddFailTableInsertFail,
                 apSecSAIMSAKASendAddToRed,
                 apSecSAIMSAKASendModToRed,
                 apSecSAIMSAKARcvdAddFromActive,
                 apSecSAIMSAKARcvdModFromActive,
                 apSecSAIMSAKASaRedAddRecFailure,
                 apSecSAIMSAKAInvalidRedAction,
                 apSecSAIMSAKASendTimedDelToRed,
                 apSecSAIMSAKARcvdTimedDelFromAct,
                 apSecSAIMSAKASAAgentSAReqTransQueueSize,
                 apSecSAIMSAKASAAgentAllowTransQuota,
                 apSecSAIMSAKASAAgentDelayDeleteCount,
                 apSecSAIMSAKASAAgentMaxTransQueueSize,
                 apSecSAIMSAKARegsTotal,
                 apSecSAIMSAKARegsFromUnprotPort,
                 apSecSAIMSAKARegsFromUnprotPortBeforeExpiry,
                 apSecSAIMSAKARegsInProtPortPriorDisconnect,
                 apSecSAIMSAKARegsOutProtPortPriorDisconnect,
                 apSecSAIMSAKAAnswerBeforeChallenge,
                 apSecSAIMSAKARegsFromPotectedPort,
                 apSecSAIMSAKARegsInitRegRejectBusy,
                 apSecSAIMSAKARegsInitRegRejectResource,
                 apSecSAIMSAKARegsInitRegFailedAllocIms,
                 apSecSAIMSAKARegsInitRegImsExist,
                 apSecSAIMSAKARegsInitRegFailedSecurityHeader,
                 apSecSAIMSAKARegsInitRegPassedQuota,
                 apSecSAIMSAKARegsReRegRejectBusy,
                 apSecSAIMSAKARegsReRegRejectResource,
                 apSecSAIMSAKARegsReRegFailedSecurityHeader,
                 apSecSAIMSAKARegsReRegNoImsEntry,
                 apSecSAIMSAKARegsReRegPassedQuota,
                 apSecSAIMSAKARegForwardUnProtectReg,
                 apSecSAIMSAKAReuseSpiFalse,
                 apSecSAIMSAKAReuseSpiTrue,
                 apSecSAIMSAKAIncompleteReg
                }
        STATUS          current
        DESCRIPTION
                "A collection of objects providing SA IMS-AKA stats"
        ::= { apSecurityGroups 22 }

apSecuritySASRTPStatsGroup  OBJECT-GROUP
        OBJECTS {
                 apSecSASRTPAddReqSent,
                 apSecSASRTPAddReqRcvd,
                 apSecSASRTPAddSuccessRespSent,
                 apSecSASRTPAddSuccessRespRcvd,
                 apSecSASRTPAddFailRespSent,
                 apSecSASRTPAddFailRespRcvd,
                 apSecSASRTPAddTransactionTimeout,
                 apSecSASRTPDelReqSent,
                 apSecSASRTPDelReqRcvd,
                 apSecSASRTPDelSuccessRespSent,
                 apSecSASRTPDelSuccessRespRcvd,
                 apSecSASRTPDelFailRespSent,
                 apSecSASRTPDelFailRespRcvd,
                 apSecSASRTPDelTransactionTimeout, 
                 apSecSASRTPModReqSent,
                 apSecSASRTPModReqRcvd,
                 apSecSASRTPModSuccessRespSent,
                 apSecSASRTPModSuccessRespRcvd,
                 apSecSASRTPModFailRespSent,
                 apSecSASRTPModFailRespRcvd,
                 apSecSASRTPModTransactionTimeout,
                 apSecSASRTPSaCreated,
                 apSecSASRTPSaCreateFailed,
                 apSecSASRTPSaDeleted,
                 apSecSASRTPSaDeleteFailed,
                 apSecSASRTPSaCollision,
                 apSecSASRTPSaKeyNotFound  
                }
        STATUS          current
        DESCRIPTION
                "A collection of objects providing SA SRTP stats"
        ::= { apSecurityGroups 23 }        

-- notification groups


apSecurityTscfStatsObjects
	OBJECT IDENTIFIER ::= {apSecurityMIBObjects 14}

apTscfActiveTunnels        OBJECT-TYPE
        SYNTAX             Gauge32
        MAX-ACCESS         read-only
        STATUS             current
        DESCRIPTION
                "Number of active TSCF tunnels"
        ::= { apSecurityTscfStatsObjects 1 }

apTscfEstablishedTunnels		  OBJECT-TYPE 
		SYNTAX                    Counter32 
		MAX-ACCESS                read-only 
		STATUS                    current
		DESCRIPTION 
				"Number of established tunnels" 
		::= {apSecurityTscfStatsObjects 2}

apTscfFinishedTunnels		  OBJECT-TYPE 
		SYNTAX            Counter32 
		MAX-ACCESS        read-only 
		STATUS            current 
		DESCRIPTION 
				"Number of finished tunnels" 
		::= {apSecurityTscfStatsObjects 3 }

apTscfReleasedTunnels		  OBJECT-TYPE 
		SYNTAX            Counter32
		MAX-ACCESS        read-only 
		STATUS            current 
		DESCRIPTION 
				"Number of released tunnels" 
		::= {apSecurityTscfStatsObjects 4   }

apTscfMaxActiveTunnels		  OBJECT-TYPE 
		SYNTAX            Counter32 
		MAX-ACCESS        read-only 
		STATUS            current 
		DESCRIPTION 
				"Number of maximum active tunnels" 
		::= {apSecurityTscfStatsObjects 5  }

apTscfConfReqReceived		   OBJECT-TYPE 
		SYNTAX             Counter32 
		MAX-ACCESS         read-only 
		STATUS             current 
		DESCRIPTION 
				"Number of config requests received" 
		::= { apSecurityTscfStatsObjects 6   }

apTscfConfReqNagleReceived		  OBJECT-TYPE 
		SYNTAX                    Counter32 
		MAX-ACCESS                read-only 
		STATUS                    current 
		DESCRIPTION 
				"Number of config requestis with  nagle received" 
		::= {apSecurityTscfStatsObjects 7  }

apTscfConfRespSent		  OBJECT-TYPE 
		SYNTAX            Counter32 
		MAX-ACCESS        read-only 
		STATUS            current 
		DESCRIPTION 
				"Number of config response sent" 
		::= {apSecurityTscfStatsObjects 8  }

apTscfConfRelReqReceived		  OBJECT-TYPE 
		SYNTAX                    Counter32 
		MAX-ACCESS                read-only 
		STATUS                    current 
		DESCRIPTION 
				"Number of config release requesast received" 
		::= { apSecurityTscfStatsObjects  9}

apTscfConfRelRespSent		  		 OBJECT-TYPE 
		SYNTAX                           Counter32 
		MAX-ACCESS                       read-only 
		STATUS                           current 
		DESCRIPTION 
				"Number of config release responses sent" 
		::= { apSecurityTscfStatsObjects 10 }

apTscfCSResponseSent		  OBJECT-TYPE 
		SYNTAX            Counter32 
		MAX-ACCESS        read-only 
		STATUS            current 
		DESCRIPTION 
				"Number of client service responses sent" 
		::= { apSecurityTscfStatsObjects 11 }

apTscfCSREnableDDT		  OBJECT-TYPE 
		SYNTAX            Counter32 
		MAX-ACCESS        read-only 
		STATUS            current 
		DESCRIPTION 
				"Number of ddt enable client service messages" 
		::= {  apSecurityTscfStatsObjects 12 }

apTscfCSRDisableDDT		  OBJECT-TYPE 
		SYNTAX            Counter32 
		MAX-ACCESS        read-only 
		STATUS            current 
		DESCRIPTION 
				"Number of ddt disable client service responses" 
		::= { apSecurityTscfStatsObjects 13  }

apTscfCSREnableRedundancy	OBJECT-TYPE 
		SYNTAX          Counter32 
		MAX-ACCESS      read-only 
		STATUS          current 
		DESCRIPTION 
				"Number of redundancy enable client service responses" 
		::= {  apSecurityTscfStatsObjects 14 }

apTscfCSRDisableRedundancy		  OBJECT-TYPE 
		SYNTAX                    Counter32 
		MAX-ACCESS                read-only 
		STATUS                    current 
		DESCRIPTION 
				"Number of redundancy disabled client service responses" 
		::= { apSecurityTscfStatsObjects 15 }

apTscfKAReceived		  OBJECT-TYPE 
		SYNTAX            Counter32 
		MAX-ACCESS        read-only 
		STATUS            current 
		DESCRIPTION 
				"Number of keep alive requests received" 
		::= { apSecurityTscfStatsObjects  16}

apTscfKARespSent		  OBJECT-TYPE 
		SYNTAX            Counter32 
		MAX-ACCESS        read-only 
		STATUS            current 
		DESCRIPTION 
				"Number of keep alive responses sent" 
		::= { apSecurityTscfStatsObjects  17}

apTscfKASent		             OBJECT-TYPE 
		SYNTAX               Counter32 
		MAX-ACCESS           read-only 
		STATUS               current 
		DESCRIPTION 
				"Number of keep alive messages sent" 
		::= { apSecurityTscfStatsObjects  18}

apTscfKARespRcvd		  OBJECT-TYPE 
		SYNTAX            Counter32 
		MAX-ACCESS        read-only 
		STATUS            current 
		DESCRIPTION 
				"Number of keep alive responses received" 
		::= { apSecurityTscfStatsObjects  19}

apTscfCMReTx		             OBJECT-TYPE 
		SYNTAX               Counter32 
		MAX-ACCESS           read-only 
		STATUS               current 
		DESCRIPTION 
				"Number of control message retransmissions" 
		::= { apSecurityTscfStatsObjects  20 }

apTscfFailureMalformed		  OBJECT-TYPE 
		SYNTAX            Counter32 
		MAX-ACCESS        read-only 
		STATUS            current 
		DESCRIPTION 
				"Number of failed tunnels due to malformed request" 
		::= {apSecurityTscfStatsObjects  21 }

apTscfFailureUnkownMsg		  OBJECT-TYPE 
		SYNTAX            Counter32 
		MAX-ACCESS        read-only 
		STATUS            current 
		DESCRIPTION 
				"Number of unknown control messages" 
		::= {  apSecurityTscfStatsObjects 22 }

apTscfFailureClientAssignedIP		  OBJECT-TYPE 
		SYNTAX                    Counter32 
		MAX-ACCESS                read-only 
		STATUS                    current 
		DESCRIPTION 
				"Number of failed tunnels due to client assigned IP" 
		::= { apSecurityTscfStatsObjects  23 }

apTscfFailureCannotProvisionIP		  OBJECT-TYPE 
		SYNTAX                    Counter32 
		MAX-ACCESS                read-only 
		STATUS                    current 
		DESCRIPTION 
				"Number of failed tunnels due to internal IP that cannot be provisioned" 
		::= { apSecurityTscfStatsObjects 24 }

apTscfFailureAlreadyProvisionedIP		  OBJECT-TYPE 
		SYNTAX                            Counter32 
		MAX-ACCESS                        read-only 
		STATUS                            current 
		DESCRIPTION 
				"Number of failed tunnels due to internal IP that are already provisioned" 
		::= {apSecurityTscfStatsObjects   25 }

apTscfFailureGeneralProvisionIP		  OBJECT-TYPE 
		SYNTAX                    Counter32 
		MAX-ACCESS                read-only 
		STATUS                    current 
		DESCRIPTION 
				"Number of failed tunnels due to general IP provision failure" 
		::= { apSecurityTscfStatsObjects  26 }

apTscfFailureClientAssignedIPMask		  OBJECT-TYPE 
		SYNTAX                            Counter32 
		MAX-ACCESS                        read-only 
		STATUS                            current 
		DESCRIPTION 
				"
                                Number of failed tunnels due to Internal IP mask assigned by client" 
		::= {apSecurityTscfStatsObjects   27 }

apTscfFailureCannotProvisionIPMask		  OBJECT-TYPE 
		SYNTAX                            Counter32 
		MAX-ACCESS                        read-only 
		STATUS                            current 
		DESCRIPTION 
				"Number of failed tunnels due to internal IP mask that cannot be  provisioned" 
		::= { apSecurityTscfStatsObjects 28 }

apTscfFailureAlreadyProvisionedIPMask		  OBJECT-TYPE 
		SYNTAX                            Counter32 
		MAX-ACCESS                        read-only 
		STATUS                            current 
		DESCRIPTION 
				"Number of failed tunnels due to Internal IP mask was  already provisioned" 
		::= { apSecurityTscfStatsObjects  29 }

apTscfFailureGeneralProvisionIPMask		  OBJECT-TYPE 
		SYNTAX                            Counter32 
		MAX-ACCESS                        read-only 
		STATUS                            current 
		DESCRIPTION 
				"Number of failed tunnels due to general IP mask provision" 
		::= { apSecurityTscfStatsObjects 30 }

apTscfFailureClientAssignedSIPServer		  OBJECT-TYPE 
		SYNTAX                            Counter32 
		MAX-ACCESS                        read-only 
		STATUS                            current 
		DESCRIPTION 
				"Number of failed tunnels due to client assigned SIP server address" 
		::= { apSecurityTscfStatsObjects 31 }

apTscfFailureCannotProvisionSIPServer		  OBJECT-TYPE 
		SYNTAX                            Counter32 
		MAX-ACCESS                        read-only 
		STATUS                            current 
		DESCRIPTION 
				"Number of failed tunnels due to unprovisioned SIP server address" 
		::= {  apSecurityTscfStatsObjects 32}

apTscfFailureAlreadyProvisionedSIPServer		  OBJECT-TYPE 
		SYNTAX                                    Counter32 
		MAX-ACCESS                                read-only 
		STATUS                                    current 
		DESCRIPTION 
				"Number of failed tunnels due to SIP server address was already provisioned" 
		::= { apSecurityTscfStatsObjects  33 }

apTscfFailureGeneralProvisionSIPServer		                  OBJECT-TYPE 
		SYNTAX                                            Counter32 
		MAX-ACCESS                                        read-only 
		STATUS                                            current 
		DESCRIPTION 
				"Number of failed tunnels due to SIP server general provision error" 
		::= { apSecurityTscfStatsObjects  34}

apTscfFailureClientAsignedKA		  OBJECT-TYPE 
		SYNTAX                    Counter32 
		MAX-ACCESS                read-only 
		STATUS                    current 
		DESCRIPTION 
				"Number of failed tunnels due to client assigned keep alive value" 
		::= {  apSecurityTscfStatsObjects  35}

apTscfFailureCannotProvisionKA		  OBJECT-TYPE 
		SYNTAX                    Counter32 
		MAX-ACCESS                read-only 
		STATUS                    current 
		DESCRIPTION 
				"Number of failed tunnels due to failure to  provision keep alive value" 
		::= { apSecurityTscfStatsObjects   36}

apTscfFailureAlreadyProvisionedKA		  OBJECT-TYPE 
		SYNTAX                            Counter32 
		MAX-ACCESS                        read-only 
		STATUS                            current 
		DESCRIPTION 
				"Number of failed tunnels due to Keep Alive value was already provisioned" 
		::= {  apSecurityTscfStatsObjects  37}

apTscfFailureGeneralProvisionKA		  OBJECT-TYPE 
		SYNTAX                    Counter32 
		MAX-ACCESS                read-only 
		STATUS                    current 
		DESCRIPTION 
				"Number of failed tunnels due to Keep alive value error" 
		::= {apSecurityTscfStatsObjects 38}

apTscfFailureNonExistentTunnelId		  OBJECT-TYPE 
		SYNTAX                            Counter32 
		MAX-ACCESS                        read-only 
		STATUS                            current 
		DESCRIPTION 
				"Number of failed tunnels due to Non existing tunnel ID" 
		::= {  apSecurityTscfStatsObjects  39}

apTscfFailureOutOfResources		  OBJECT-TYPE 
		SYNTAX                    Counter32 
		MAX-ACCESS                read-only 
		STATUS                    current 
		DESCRIPTION 
				"Number of failed tunnels due to out of resources" 
		::= {apSecurityTscfStatsObjects   40}

apTscfFailureInternalIPExhausted		  OBJECT-TYPE 
		SYNTAX                            Counter32 
		MAX-ACCESS                        read-only 
		STATUS                            current 
		DESCRIPTION 
				"Number of failed tunnels due to tunnel ID depletion" 
		::= {apSecurityTscfStatsObjects   41}

apTscfFailureNonNullIPAddr		  OBJECT-TYPE 
		SYNTAX                    Counter32 
		MAX-ACCESS                read-only 
		STATUS                    current 
		DESCRIPTION 
				"Number of failed tunnels due to non null ip address " 
		::= {  apSecurityTscfStatsObjects  42}

apTscfFailureNonNullIpMask		  OBJECT-TYPE 
		SYNTAX                    Counter32 
		MAX-ACCESS                read-only 
		STATUS                    current 
		DESCRIPTION 
				"Number of  failed tunnels due to non null ip mask" 
		::= {apSecurityTscfStatsObjects  43 }

apTscfFailureNonNullSipServer		  OBJECT-TYPE 
		SYNTAX                    Counter32 
		MAX-ACCESS                read-only 
		STATUS                    current 
		DESCRIPTION 
				"Number of failed tunnels due to non null sip server" 
		::= {apSecurityTscfStatsObjects  44 }

apTscfFailureNonNullKeepAlive		  OBJECT-TYPE 
		SYNTAX                    Counter32 
		MAX-ACCESS                read-only 
		STATUS                    current 
		DESCRIPTION 
				"Number of failed tunnels due to non zero Keep Alive value" 
		::= { apSecurityTscfStatsObjects  45 }

apTscfFailureNoListeningFd		  OBJECT-TYPE 
		SYNTAX                    Counter32 
		MAX-ACCESS                read-only 
		STATUS                    current 
		DESCRIPTION 
				"Number of failed tunnels due to missing  listening file descriptor" 
		::= { apSecurityTscfStatsObjects  46}

apTscfFailureServerFailure		  OBJECT-TYPE 
		SYNTAX                    Counter32 
		MAX-ACCESS                read-only 
		STATUS                    current 
		DESCRIPTION 
				"Number of failed tunnels due to server failure" 
		::= {apSecurityTscfStatsObjects   47}

apTscfFailureRedundancyNotEnabled		  OBJECT-TYPE 
		SYNTAX                            Counter32 
		MAX-ACCESS                        read-only 
		STATUS                            current 
		DESCRIPTION 
				"Number of failed tunnels due to  disabled redundancy feature" 
		::= {apSecurityTscfStatsObjects  48 }

apTscfFailureRedundancyExceedsLimit		  OBJECT-TYPE 
		SYNTAX                            Counter32 
		MAX-ACCESS                        read-only 
		STATUS                            current 
		DESCRIPTION 
				"Number of failed tunnels due to redundancy factor exceediing the limit" 
		::= { apSecurityTscfStatsObjects  49}

apTscfFailureTunnelIdExhausted		  OBJECT-TYPE 
		SYNTAX                    Counter32 
		MAX-ACCESS                read-only 
		STATUS                    current 
		DESCRIPTION 
				"Number of failed tunnels due to tunnel id exhaustion" 
		::= { apSecurityTscfStatsObjects  50}

apTscfFailureTimerFailure		  OBJECT-TYPE 
		SYNTAX                    Counter32 
		MAX-ACCESS                read-only 
		STATUS                    current 
		DESCRIPTION 
				"Number of failed tunnels due to Timer failure" 
		::= {apSecurityTscfStatsObjects   51}

apTscfFailureDDTNotEnabled		  OBJECT-TYPE 
		SYNTAX                    Counter32 
		MAX-ACCESS                read-only 
		STATUS                    current 
		DESCRIPTION 
				"Failure due to DDT disabled" 
		::= { apSecurityTscfStatsObjects  52}

apTscfFailureDDTWrongTransport		  OBJECT-TYPE 
		SYNTAX                    Counter32 
		MAX-ACCESS                read-only 
		STATUS                    current 
		DESCRIPTION 
				"Failure due to DDT wrong transport" 
		::= { apSecurityTscfStatsObjects  53}

apTscfFailureDDTDatagramOnly		  OBJECT-TYPE 
		SYNTAX                    Counter32 
		MAX-ACCESS                read-only 
		STATUS                    current 
		DESCRIPTION 
				"Number of failed tunnels due to DDT request on datagram transport" 
		::= { apSecurityTscfStatsObjects  54}

apTscfFailureDDTInconsistantTransport		  OBJECT-TYPE 
		SYNTAX                            Counter32 
		MAX-ACCESS                        read-only 
		STATUS                            current 
		DESCRIPTION 
				"Number of failed tunnels due inconsistent DDT transport" 
		::= {apSecurityTscfStatsObjects   55}

apTscfFailureUnkownServiceRequest		  OBJECT-TYPE 
		SYNTAX                            Counter32 
		MAX-ACCESS                        read-only 
		STATUS                            current 
		DESCRIPTION 
				"Number of failed tunnels due to unknown service request" 
		::= {apSecurityTscfStatsObjects  56 }

apTscfFailureTunnelEstablished		  OBJECT-TYPE 
		SYNTAX                    Counter32 
		MAX-ACCESS                read-only 
		STATUS                    current 
		DESCRIPTION 
				"Number of tunnel establishment failure" 
		::= {apSecurityTscfStatsObjects  57 }

apTscfFailureAddrPoolUnavilable		  OBJECT-TYPE 
		SYNTAX                    Counter32 
		MAX-ACCESS                read-only 
		STATUS                    current 
		DESCRIPTION 
				"Number of failed tunnels due to unavailable address pool" 
		::= { apSecurityTscfStatsObjects  58}

apTscfFailureListenFdUnavailable		  OBJECT-TYPE 
		SYNTAX                            Counter32 
		MAX-ACCESS                        read-only 
		STATUS                            current 
		DESCRIPTION 
				"Number of failed tunnels due to missing listening file descriptor" 
		::= { apSecurityTscfStatsObjects  59}

apTscfFailureVersionNotSupported		  OBJECT-TYPE 
		SYNTAX                            Counter32 
		MAX-ACCESS                        read-only 
		STATUS                            current 
		DESCRIPTION 
				"Number of failed tunnels due to unsupported version" 
		::= {  apSecurityTscfStatsObjects 60}

apTscfFailureLicenseExceeded		  OBJECT-TYPE 
		SYNTAX                    Counter32 
		MAX-ACCESS                read-only 
		STATUS                    current 
		DESCRIPTION 
				"Number of failed tunnels due to exceeding the licensed/entitled  limit" 
		::= { apSecurityTscfStatsObjects  61}

apTscfFailureNoTunnelForPkt		  OBJECT-TYPE 
		SYNTAX                    Counter32 
		MAX-ACCESS                read-only 
		STATUS                    current 
		DESCRIPTION 
				"Number of packets dropped due to missing tunnel" 
		::= {apSecurityTscfStatsObjects  62}

apTscfWrongSeqNum	    	  OBJECT-TYPE 
		SYNTAX            Counter32 
		MAX-ACCESS        read-only 
		STATUS            current 
		DESCRIPTION 
				"Number of control messages with wrong sequence number" 
		::= { apSecurityTscfStatsObjects  63}

apTscfConDrop		             OBJECT-TYPE 
		SYNTAX               Counter32 
		MAX-ACCESS           read-only 
		STATUS               current 
		DESCRIPTION 
				"Number of config requests dropped due to license limit" 
		::= { apSecurityTscfStatsObjects  64}

apTscfIntfConDrop		  OBJECT-TYPE 
		SYNTAX            Counter32 
		MAX-ACCESS        read-only 
		STATUS            current 
		DESCRIPTION 
				"Number of config requests dropped due to per interface limit" 
		::= {apSecurityTscfStatsObjects   65}

apTscfStatsAllocs		  OBJECT-TYPE 
		SYNTAX            Counter32 
		MAX-ACCESS        read-only 
		STATUS            current 
		DESCRIPTION 
				"Number of Stats memory allocations" 
		::= { apSecurityTscfStatsObjects  66}

apTscfStatsFrees		  OBJECT-TYPE 
		SYNTAX            Counter32 
		MAX-ACCESS        read-only 
		STATUS            current 
		DESCRIPTION 
				"Number of Stats memory frees" 
		::= {apSecurityTscfStatsObjects   67}

apTscfStatsMemFails		  OBJECT-TYPE 
		SYNTAX            Counter32 
		MAX-ACCESS        read-only 
		STATUS            current 
		DESCRIPTION 
				"Stats memory allocation failures" 
		::= { apSecurityTscfStatsObjects  68}

apTscfSwitchToActive		  OBJECT-TYPE 
		SYNTAX            Counter32 
		MAX-ACCESS        read-only 
		STATUS            current 
		DESCRIPTION 
				"Number of times system switched to active system" 
		::= {apSecurityTscfStatsObjects   69}

apTscfSwitchToStandBy		  OBJECT-TYPE 
		SYNTAX            Counter32 
		MAX-ACCESS        read-only 
		STATUS            current 
		DESCRIPTION 
				"Number of times system switched to stand by system" 
		::= {  apSecurityTscfStatsObjects  70}

apTscfGetDTLSCtxSent		  OBJECT-TYPE 
		SYNTAX            Counter32 
		MAX-ACCESS        read-only 
		STATUS            current 
		DESCRIPTION 
				"Number of get DTLS context requests sent" 
		::= {apSecurityTscfStatsObjects  71 }

apTscfGetDTLSCtxSuccess		  OBJECT-TYPE 
		SYNTAX            Counter32 
		MAX-ACCESS        read-only 
		STATUS            current 
		DESCRIPTION 
				"Number of successful get DTLS context requests" 
		::= {apSecurityTscfStatsObjects   72}

apTscfGetDTLSCtxFailed		  OBJECT-TYPE 
		SYNTAX            Counter32 
		MAX-ACCESS        read-only 
		STATUS            current 
		DESCRIPTION 
				"Number of failed get DTLS context requests" 
		::= {apSecurityTscfStatsObjects   73}

apTscfSetDTLSCtxSent		  OBJECT-TYPE 
		SYNTAX            Counter32 
		MAX-ACCESS        read-only 
		STATUS            current 
		DESCRIPTION 
				"Number of set DTLS context requests sent" 
		::= { apSecurityTscfStatsObjects  74}

apTscfSetDTLSCtxSuccess		  OBJECT-TYPE 
		SYNTAX            Counter32 
		MAX-ACCESS        read-only 
		STATUS            current 
		DESCRIPTION 
				"Number of successful DTLS context requests" 
		::= {apSecurityTscfStatsObjects   75}

apTscfSetDTLSCtxFailed		  OBJECT-TYPE 
		SYNTAX            Counter32 
		MAX-ACCESS        read-only 
		STATUS            current 
		DESCRIPTION 
				"Number of failed set DTLS context request" 
		::= {apSecurityTscfStatsObjects  76 }

apTscfFdTableSize		  OBJECT-TYPE 
		SYNTAX            Gauge32 
		MAX-ACCESS        read-only 
		STATUS            current 
		DESCRIPTION 
				"Number of entries in the File Descriptor table" 
		::= {apSecurityTscfStatsObjects   77}

apTscfAddressTableSize		  OBJECT-TYPE 
		SYNTAX            Gauge32 
		MAX-ACCESS        read-only 
		STATUS            current 
		DESCRIPTION 
				"Number of entries in the Address table" 
		::= { apSecurityTscfStatsObjects  78}

apTscfTunnelTableSize		  OBJECT-TYPE 
		SYNTAX            Gauge32 
		MAX-ACCESS        read-only 
		STATUS            current 
		DESCRIPTION 
				"Number of entries in the Tunnel table" 
		::= {apSecurityTscfStatsObjects  79 }

apTscfActiveTunnelTableSize		  OBJECT-TYPE 
		SYNTAX                    Gauge32 
		MAX-ACCESS                read-only 
		STATUS                    current 
		DESCRIPTION 
				"Number of entries in the Active Tunnel table" 
		::= {apSecurityTscfStatsObjects   80}

apTscfFlowIdTableSize		  OBJECT-TYPE 
		SYNTAX            Gauge32 
		MAX-ACCESS        read-only 
		STATUS            current 
		DESCRIPTION 
				"Number of entries in the Flow table" 
		::= {apSecurityTscfStatsObjects   81}

apTscfLicenseTunnelCount		  OBJECT-TYPE 
		SYNTAX                    Gauge32 
		MAX-ACCESS                read-only 
		STATUS                    current 
		DESCRIPTION 
				"Number of Licensed/entitled tunnels " 
		::= { apSecurityTscfStatsObjects  82}

apTscfSpecificAddressCount		  OBJECT-TYPE 
		SYNTAX                    Counter32 
		MAX-ACCESS                read-only 
		STATUS                    current 
		DESCRIPTION 
				"Number of requests for specific IP adddress" 
		::= { apSecurityTscfStatsObjects  83}

apTscfTunnelTimeoutCount		  OBJECT-TYPE 
		SYNTAX                    Counter32 
		MAX-ACCESS                read-only 
		STATUS                    current 
		DESCRIPTION 
				"Total number of timed outi tunnels" 
		::= { apSecurityTscfStatsObjects  84}

apTscfTunneledPacketDrop             OBJECT-TYPE 
		SYNTAX               Counter32 
		MAX-ACCESS           read-only 
		STATUS               current 
		DESCRIPTION 
				"Total number of tunneled packet drops" 
		::= { apSecurityTscfStatsObjects  85}

apTscfUnTunneledPacketDrop		  OBJECT-TYPE 
		SYNTAX                    Counter32 
		MAX-ACCESS                read-only 
		STATUS                    current 
		DESCRIPTION 
				"Total number of untunneled packet drops" 
		::= {apSecurityTscfStatsObjects  86}

apTscfCsrReceived		  OBJECT-TYPE 
		SYNTAX            Counter32 
		MAX-ACCESS        read-only 
		STATUS            current 
		DESCRIPTION 
				"Total number of Client service requests received" 
		::= {apSecurityTscfStatsObjects  87}

apTscfTypeInnerIPDestDrop                 OBJECT-TYPE 
                SYNTAX                    Counter32 
                MAX-ACCESS                read-only 
                STATUS                    current 
                DESCRIPTION 
                               "Number of packets dropped due to inner IP destination match with address pool" 
                ::= {apSecurityTscfStatsObjects  88}

apTscfTunnelsTimedOut                      OBJECT-TYPE 
                SYNTAX                    Counter32 
                MAX-ACCESS                read-only 
                STATUS                    current 
                DESCRIPTION 
                               "Number of tunnels dropped due to timing out" 
                ::= {apSecurityTscfStatsObjects  89}


-- TSCF ADDRESS POOL STATISTICS

apSecurityTscfAddressPoolStatsTable OBJECT-TYPE
        SYNTAX          SEQUENCE OF ApSecurityTscfAddressPoolStatsEntry
        MAX-ACCESS      not-accessible
        STATUS          current
        DESCRIPTION
                "The table of TSCF address pool statistics."
        ::= { apSecurityMIBObjects 15 }


apSecurityTscfAddressPoolStatsEntry OBJECT-TYPE
        SYNTAX          ApSecurityTscfAddressPoolStatsEntry
        MAX-ACCESS      not-accessible
        STATUS          current
        DESCRIPTION
                "TSCF Address pool statistics."
        INDEX   { apSecurityTscfAddressPoolName }
        ::= { apSecurityTscfAddressPoolStatsTable 1 }

ApSecurityTscfAddressPoolStatsEntry ::=
        SEQUENCE {
                apSecurityTscfAddressPoolName                    DisplayString,
                apSecurityTscfTotalAddressCount                  Gauge32,
                apSecurityTscfInUseAddressCount                  Gauge32,
                apSecurityTscfFreeAddressCount                   Gauge32,
                apSecurityTscfInvalidAddressCount                Gauge32
                }

apSecurityTscfAddressPoolName                    OBJECT-TYPE
        SYNTAX                  DisplayString (SIZE (0..255))
        MAX-ACCESS              accessible-for-notify
        STATUS                  current
        DESCRIPTION
                "The name of the TSCF Address Pool"
        ::= { apSecurityTscfAddressPoolStatsEntry 1}

apSecurityTscfTotalAddressCount     OBJECT-TYPE
        SYNTAX               Gauge32
        MAX-ACCESS           accessible-for-notify
        STATUS               current
        DESCRIPTION
                "The total numbers of addresses in the TSCF address pool"
        ::= { apSecurityTscfAddressPoolStatsEntry 2 }

apSecurityTscfInUseAddressCount                  OBJECT-TYPE
        SYNTAX               Gauge32
        MAX-ACCESS           accessible-for-notify
        STATUS               current
        DESCRIPTION
                "The number of addresses in use from the TSCF address pool"
        ::= { apSecurityTscfAddressPoolStatsEntry 3 }

apSecurityTscfFreeAddressCount                     OBJECT-TYPE
        SYNTAX               Gauge32
        MAX-ACCESS           accessible-for-notify
        STATUS               current
        DESCRIPTION
                "The number of addresses available for allocation in the TSCF address pool"
        ::= { apSecurityTscfAddressPoolStatsEntry 4 }

apSecurityTscfInvalidAddressCount                 OBJECT-TYPE
        SYNTAX               Gauge32
        MAX-ACCESS           accessible-for-notify
        STATUS               current
        DESCRIPTION
                "The number of invalid  addresses in the TSCF address pool"
        ::= { apSecurityTscfAddressPoolStatsEntry 5 }


-- TSCF notifications

    apSecurityTscfAddrPoolThresholdLevel     OBJECT-TYPE
        SYNTAX          Gauge32
        MAX-ACCESS      accessible-for-notify
        STATUS          current
        DESCRIPTION
            "TSCF address pool threshold"
        ::= { apSecurityNotificationObjects 29 }

    apSecurityTscfMaxTunnelsThresholdLevel   OBJECT-TYPE
        SYNTAX          Gauge32
        MAX-ACCESS      accessible-for-notify
        STATUS          current
        DESCRIPTION
            "TSCF max tunnels threshold"
        ::= { apSecurityNotificationObjects 30 }

    apSecurityTscfNotificationsPrefix
                OBJECT IDENTIFIER ::= { apSecurityNotifications 8 }

    apSecurityTscfNotifications
                OBJECT IDENTIFIER ::= { apSecurityTscfNotificationsPrefix 0 }


    apSecurityTscfAddressPoolUsageTrap   NOTIFICATION-TYPE
        OBJECTS
        {
                        apSecurityTscfAddressPoolName, 
                        apSecurityTscfInUseAddressCount,
                        apSecurityTscfTotalAddressCount,
                        apSecurityTscfAddrPoolThresholdLevel
        }
        STATUS          current
        DESCRIPTION
                        "This notification is sent when the available IP addresses
                        in TSCF address pool depletes below the 
                        threshold level."
                
        ::= { apSecurityTscfNotifications 1 }


    apSecurityTscfAddressPoolUsageClearTrap  NOTIFICATION-TYPE
        OBJECTS
        {
                        apSecurityTscfAddressPoolName, 
                        apSecurityTscfInUseAddressCount,
                        apSecurityTscfTotalAddressCount,
                        apSecurityTscfAddrPoolThresholdLevel
        }
        STATUS          current
        DESCRIPTION
                        "This notification is sent when the available 
                        IP addresses in TSCF address pool 
                        are more than the threshold level."
                
        ::= { apSecurityTscfNotifications 2 }

    apSecurityTscfMaxTunnelTrap  NOTIFICATION-TYPE
        OBJECTS
        {
                        apTscfActiveTunnels,
                        apTscfLicenseTunnelCount,
                        apSecurityTscfMaxTunnelsThresholdLevel
        }
        STATUS          current
        DESCRIPTION
                        "This notification is sent when the available
                        IP addresses in TSCF address pool 
                        depletes below the threshold level."
                
        ::= { apSecurityTscfNotifications 3 }

    apSecurityTscfClearMaxTunnelTrap  NOTIFICATION-TYPE
        OBJECTS
        {
                        apTscfActiveTunnels,
                        apTscfLicenseTunnelCount,
                        apSecurityTscfMaxTunnelsThresholdLevel
        }
        STATUS          current
        DESCRIPTION
                        "This notification is sent when the available
                        IP addresses in TSCF address pool 
                        depletes below the threshold level."
                
        ::= { apSecurityTscfNotifications 4 }

    apSecurityTscfNotificationsGroup  NOTIFICATION-GROUP
        NOTIFICATIONS
        {
                apSecurityTscfAddressPoolUsageTrap,
                apSecurityTscfAddressPoolUsageClearTrap,
                apSecurityTscfMaxTunnelTrap,
                apSecurityTscfClearMaxTunnelTrap
                }
        STATUS                           current
        DESCRIPTION
                 "A collection of notifications for TSCF resource alerts"
        ::= {  apSecurityNotificationsGroups 11 }

END
