----------------------------------------------------------------------
-- ACMEPACKET-SMI.mIB:  Acme packet Enterprise Structure of Management
-- Information
--
-- February 2001, pzhou
--
-- Copyright by Oracle Communications
-- All rights reserved.
-- 
------------------------------------------------------------------------

ACMEPACKET-SMI DEFINITIONS ::= BEGIN

IMPORTS
	MODULE-IDENTITY,
	OBJECT-IDENTITY,
	enterprises
		FROM SNMPv2-SMI;

acmepacket MODULE-IDENTITY
        LAST-UPDATED	"201406260000Z"
        ORGANIZATION 	"Oracle Communications"
        CONTACT-INFO
			"           	Customer Service
		 	Postal:		Oracle Communications
					100 Crosby Drive 
					Bedford, MA 01730
					US
		    	Tel:		1-800-633-0738
			Url:		www.oracle.com
		 	E-mail:		support@oracle.com"
	DESCRIPTION
		"Structure of Managed Information for Acme Packet Inc."
	REVISION      "201202021800Z"
	DESCRIPTION
		"Updated new contact info."
	REVISION      "200402261800Z"
	DESCRIPTION
		"The Structure of Management Information for the
		Acme Packet enterprise. Add acmepacketModules."
	REVISION      "200109050000Z"
	DESCRIPTION
		"Initial version of this MIB module."
	REVISION 	"201406260000Z" 			
        DESCRIPTION
	        "Updated Organization and Contact info."
	::= { enterprises 9148 }	-- assigned by IANA


-- Duplicated Definition with acmepacketProducts in ap-products.mib 
-- Commented out to avoid mibble compiler error warning messages. 
-- No impact on Envoy compiler in SBC side.
--
--acmepacketProducts OBJECT-IDENTITY
--	STATUS	current
--	DESCRIPTION
--		"acmepacketProducts is the root OBJECT IDENTIFIER from
--		which sysObjectID values are assigned.  This is reserved
--		for future use."
--	::= { acmepacket 1 }

acmepacketAgentCapability OBJECT-IDENTITY
	STATUS	current
	DESCRIPTION
		"acmepacketAgentCapability provides a root object identifier
		from which AGENT-CAPABILITIES values may be assigned."
	::= { acmepacket 2 }

acmepacketMgmt OBJECT-IDENTITY
	STATUS	current
	DESCRIPTION
		"acmepacketMgmt is the main subtree for the management."
	::= { acmepacket 3 }

acmepacketConfig OBJECT-IDENTITY
	STATUS	current
	DESCRIPTION
		"acmepacketConfig is the subtree for configuration mibs. 
		This is reserved for future use."
	::= { acmepacket 4 }


acmepacketExperiment OBJECT-IDENTITY
	STATUS	current
	DESCRIPTION
		"acmepacketExperiment provides a root object identifier
		from which experimental mibs may be temporarily
		based. support for mibs in the acmepacketExperiment
		subtree will be deleted when a permanent object
		identifier assignment is made. This is reserved 
		for future use."
	::= { acmepacket 5 }

acmepacketModules OBJECT-IDENTITY
	STATUS	current
	DESCRIPTION
		"acmepacketModules provides a root object identifier
		from which MODULE-IDENTITY values may be assigned."
	::= { acmepacket 6 }

END
