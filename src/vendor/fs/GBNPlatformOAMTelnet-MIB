------------------------------------------------------------------------------
--
--  File              : gbnPlatformOAMTelnet-MIB.mi2
--  Description       : Telnet configuration MIB 
--  Version           : 1.0  
--  Date              : April 16, 2013     
--  Author            : tangrenxiang
--  Copyright (c) 2001-2008 admin Co. Ltd.  All Rights Reserved.
--
------------------------------------------------------------------------------

    GBNPlatformOAMTelnet-MIB DEFINITIONS ::= BEGIN

    IMPORTS
        MODULE-IDENTITY, OBJECT-TYPE,
        Counter32, Gauge32,
        Unsigned32, Integer32,
        IpAddress, NOTIFICATION-TYPE            FROM SNMPv2-SMI
        
        RowStatus, TruthValue, 
        DisplayString, MacAddress               FROM SNMPv2-TC
        
        MODULE-COMPLIANCE, OBJECT-GROUP         FROM SNMPv2-CONF
        
        snmpTraps                               FROM SNMPv2-MIB
        
        gbnPlatformOAM                          FROM GBNPlatformOAM-MIB;
    
    gbnPlatformOAMTelnet  MODULE-IDENTITY
        LAST-UPDATED    "1304160000Z"  -- April 16, 2013
        ORGANIZATION    "admin Co. Ltd"
        CONTACT-INFO    "admin Co. Ltd
                         E-mail: service@admin.com.cn"

        DESCRIPTION     "Telnet mib definition."

        REVISION        "1304160000Z"  -- April 16, 2013
        DESCRIPTION     "Initial MIB creation."

        ::= { gbnPlatformOAM 15 }
        
	telnetState OBJECT-TYPE
        SYNTAX INTEGER {
            enable(1),
            disable(2)
        }
        MAX-ACCESS read-write
        STATUS current
        DESCRIPTION
            "enable or disable telnet."
            --telnet
        ::= { gbnPlatformOAMTelnet 1 } 

  telnetUserLimit OBJECT-TYPE
        SYNTAX Integer32 (0..5)
        MAX-ACCESS read-write
        STATUS current
        DESCRIPTION
            "The max user limit of telnet"
            --telnet
        ::= { gbnPlatformOAMTelnet 2 }               
   
  telnetLoginUsers  OBJECT-TYPE
        SYNTAX Counter32 
        MAX-ACCESS read-only
        STATUS current
        DESCRIPTION
            "Current login users of telnet"
            --telnet
        ::= { gbnPlatformOAMTelnet 3 }
  
  telnetUserTable OBJECT-TYPE
        SYNTAX SEQUENCE OF TelnetUserEntry
        MAX-ACCESS not-accessible
        STATUS current
        DESCRIPTION
            "A table of  login user information"
            --
        ::= { gbnPlatformOAMTelnet 4 }

  telnetUserEntry OBJECT-TYPE
        SYNTAX TelnetUserEntry
        MAX-ACCESS not-accessible
        STATUS current
        DESCRIPTION
            "A list of login user information"
            --
        INDEX { telnetUserTerminal }
        ::= { telnetUserTable 1 }

  TelnetUserEntry ::= SEQUENCE {
            telnetUserTerminal     Counter32,
            telnetUserAddrIp       DisplayString,
            telnetUserName         DisplayString,
            telnetUserLoginTime    DisplayString,
            telnetUserTransport    DisplayString,
            telnetUserRowStatus    RowStatus
        } 
  
  telnetUserTerminal OBJECT-TYPE
        SYNTAX Counter32
        MAX-ACCESS read-only
        STATUS current
        DESCRIPTION
            "login terminal number"
            --
        ::= { telnetUserEntry 1 }
 
  telnetUserAddrIp OBJECT-TYPE
        SYNTAX DisplayString(SIZE(1..64))
        MAX-ACCESS read-only
        STATUS current
        DESCRIPTION
            "login ip address"
            -- ip,IPV4IPV6.
        ::= { telnetUserEntry 2 }

  telnetUserName OBJECT-TYPE
        SYNTAX DisplayString (SIZE(1..32))
        MAX-ACCESS read-only
        STATUS current
        DESCRIPTION
            "login user name"
            --
        ::= { telnetUserEntry 3 }

  telnetUserLoginTime OBJECT-TYPE
        SYNTAX DisplayString (SIZE(0..100))
        MAX-ACCESS read-only
        STATUS current
        DESCRIPTION
            "login time"
            --
        ::= { telnetUserEntry 4 } 
        
  telnetUserTransport OBJECT-TYPE
        SYNTAX DisplayString (SIZE(0..20))
        MAX-ACCESS read-only
        STATUS current
        DESCRIPTION
            "transport type"
            --, telnetssh
        ::= { telnetUserEntry 5 }
        
  telnetUserRowStatus OBJECT-TYPE
        SYNTAX RowStatus
        MAX-ACCESS read-write
        STATUS current
        DESCRIPTION
            "login user rowstatus"
            --
        ::= { telnetUserEntry 6 }                                        
   END
