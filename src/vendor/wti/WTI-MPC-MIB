--
 -- Copyright(C) 2008 Western Telematic, Inc.
 --
        WTI-MPC-MIB DEFINITIONS ::= BEGIN

        IMPORTS
        MODULE-IDENTITY, NOTIFICATION-TYPE,
        OBJECT-TYPE, enterprises FROM SNMPv2-SMI
        DisplayString FROM SNMPv2-TC;
        westernTelematic OBJECT IDENTIFIER ::= { enterprises 2634 }

        wti MODULE-IDENTITY
                LAST-UPDATED "200812171530Z" -- 17 Dec 2008
                ORGANIZATION "Western Telematic, Inc."
                CONTACT-INFO
                "Western Telematic, Inc.
		5 Sterling
		Irvine, Ca 92618
		Email: anthonyb@wti.com"
                DESCRIPTION
                        "This is the MIB module for the MPC"

                REVISION "200812171530Z" -- 17 Dec 2008

                DESCRIPTION
                        "V3.00 for the MPC 1.60"

        ::= { westernTelematic 3 }

        --
        -- System Tables
        --

        systemTables OBJECT IDENTIFIER ::= { wti 100 }
        --
        -- Plug Table
        --

        plugTable OBJECT-TYPE
                SYNTAX SEQUENCE OF PlugEntry
                MAX-ACCESS not-accessible
                STATUS current
                DESCRIPTION
                        "A table of plugs."
        ::= { systemTables 200 }

        plugEntry OBJECT-TYPE
                SYNTAX PlugEntry
                MAX-ACCESS not-accessible
                STATUS current
                DESCRIPTION
                        "Row definition for the plug table."
                INDEX { plugIndex }
        ::= { plugTable 1 }

        PlugEntry ::= SEQUENCE {
                plugIndex INTEGER,
                plugID DisplayString,
                plugStatus INTEGER,
                plugAction INTEGER,
                plugName DisplayString
        }

        plugIndex OBJECT-TYPE
                SYNTAX INTEGER (0..80)
                MAX-ACCESS not-accessible
                STATUS current
                DESCRIPTION
                        "Index for the plug table."
        ::= { plugEntry 1 }

        plugID OBJECT-TYPE
                SYNTAX DisplayString(SIZE(9..11))
                MAX-ACCESS read-only
                STATUS current
                DESCRIPTION
                        "The ID of the plug."
        ::= { plugEntry 2 }

        plugStatus OBJECT-TYPE
                SYNTAX INTEGER (0..1)
                MAX-ACCESS read-only
                STATUS current
                DESCRIPTION
                        "Plug status"
        ::= { plugEntry 3 }

        plugAction OBJECT-TYPE
                SYNTAX INTEGER (0..8)
                MAX-ACCESS read-write
                STATUS current
                DESCRIPTION
                        "Plug action"
        ::= { plugEntry 4 }

        plugName OBJECT-TYPE
                SYNTAX DisplayString
                MAX-ACCESS read-only
                STATUS current
                DESCRIPTION
                        "The Name of the plug."
        ::= { plugEntry 5 }

        --
        -- Plug Group Table
        --

        plugGroupTable OBJECT-TYPE
                SYNTAX SEQUENCE OF PlugGroupEntry
                MAX-ACCESS not-accessible
                STATUS current
                DESCRIPTION
                        "A table of plug groups."
        ::= { systemTables 300 }

        plugGroupEntry OBJECT-TYPE
                SYNTAX PlugGroupEntry
                MAX-ACCESS not-accessible
                STATUS current
                DESCRIPTION
                        "Row definition for the plug group table."
                INDEX { plugGroupIndex }
        ::= { plugGroupTable 1 }

        PlugGroupEntry ::= SEQUENCE {
                plugGroupIndex INTEGER,
                plugGroupName DisplayString,
                plugGroupAction INTEGER
        }

        plugGroupIndex OBJECT-TYPE
                SYNTAX INTEGER (0..54)
                MAX-ACCESS not-accessible
                STATUS current
                DESCRIPTION
                        "Index for the plug group table."
        ::= { plugGroupEntry 1 }

        plugGroupName OBJECT-TYPE
                SYNTAX DisplayString(SIZE(1..24))
                MAX-ACCESS read-only
                STATUS current
                DESCRIPTION
                        "The name of the plug group."
        ::= { plugGroupEntry 2 }

        plugGroupAction OBJECT-TYPE
                SYNTAX INTEGER (0..8)
                MAX-ACCESS read-write
                STATUS current
                DESCRIPTION
                        "Plug group action"
        ::= { plugGroupEntry 3 }

        --
        -- User Table
        --

        userTable OBJECT-TYPE
                SYNTAX SEQUENCE OF UserEntry
                MAX-ACCESS not-accessible
                STATUS current
                DESCRIPTION
                        "A table of users."
        ::= { systemTables 400 }

        userEntry OBJECT-TYPE
                SYNTAX UserEntry
                MAX-ACCESS not-accessible
                STATUS current
                DESCRIPTION
                        "Row definition for the user table."
                INDEX { userIndex }
        ::= { userTable 1 }

        UserEntry ::= SEQUENCE {
                userIndex INTEGER,
                userName DisplayString,
                userPasswd DisplayString,
                userAccessLevel INTEGER,
                userPortAccess DisplayString,
                userLocalAccess DisplayString,
                userAux1Access DisplayString,
                userAux2Access DisplayString,
                userAux3Access DisplayString,
                userGroupAccess DisplayString,
                userSerialAccess INTEGER,
                userTelnetSshAccess INTEGER,
                userWebAccess INTEGER,
                userCurrentPowerMetering INTEGER,
                userCallbackNum DisplayString,
                userSubmit INTEGER
        }

        userIndex OBJECT-TYPE
                SYNTAX INTEGER (0..128)
                MAX-ACCESS not-accessible
                STATUS current
                DESCRIPTION
                        "Index for the user table."
        ::= { userEntry 1 }

        userName OBJECT-TYPE
                SYNTAX DisplayString(SIZE(0..32))
                MAX-ACCESS read-write
                STATUS current
                DESCRIPTION
                        "The name of the user."
        ::= { userEntry 2 }

        userPasswd OBJECT-TYPE
                SYNTAX DisplayString(SIZE(1..16))
                MAX-ACCESS read-write
                STATUS current
                DESCRIPTION
                        "The password of the user."
        ::= { userEntry 3 }

        userAccessLevel OBJECT-TYPE
                SYNTAX INTEGER (0..3)
                MAX-ACCESS read-write
                STATUS current
                DESCRIPTION
                        "Users access level"
        ::= { userEntry 4 }

        userPortAccess OBJECT-TYPE
                SYNTAX DisplayString(SIZE(1..5))
                MAX-ACCESS read-write
                STATUS current
                DESCRIPTION
                        "Access to ports."
        ::= { userEntry 5 }

        userLocalAccess OBJECT-TYPE
                SYNTAX DisplayString(SIZE(1..20))
                MAX-ACCESS read-write
                STATUS current
                DESCRIPTION
                        "Access to LOCAL plugs."
        ::= { userEntry 6 }

        userAux1Access OBJECT-TYPE
                SYNTAX DisplayString(SIZE(1..20))
                MAX-ACCESS read-write
                STATUS current
                DESCRIPTION
                        "Access to AUX1 plugs."
        ::= { userEntry 7 }

        userAux2Access OBJECT-TYPE
                SYNTAX DisplayString(SIZE(1..20))
                MAX-ACCESS read-write
                STATUS current
                DESCRIPTION
                        "Access to AUX2 plugs."
        ::= { userEntry 8 }

        userAux3Access OBJECT-TYPE
                SYNTAX DisplayString(SIZE(1..20))
                MAX-ACCESS read-write
                STATUS current
                DESCRIPTION
                        "Access to AUX3 plugs."
        ::= { userEntry 9 }

        userGroupAccess OBJECT-TYPE
                SYNTAX DisplayString(SIZE(1..54))
                MAX-ACCESS read-write
                STATUS current
                DESCRIPTION
                        "Access to plug groups."
        ::= { userEntry 10 }

        userSerialAccess OBJECT-TYPE
                SYNTAX INTEGER (0..1)
                MAX-ACCESS read-write
                STATUS current
                DESCRIPTION
                        "Access to serial interface."
        ::= { userEntry 11 }

        userTelnetSshAccess OBJECT-TYPE
                SYNTAX INTEGER (0..1)
                MAX-ACCESS read-write
                STATUS current
                DESCRIPTION
                        "Access to Telnet/SSH interface."
        ::= { userEntry 12 }

        userWebAccess OBJECT-TYPE
                SYNTAX INTEGER (0..1)
                MAX-ACCESS read-write
                STATUS current
                DESCRIPTION
                        "Access to web interface."
        ::= { userEntry 13 }

        userCurrentPowerMetering OBJECT-TYPE
                SYNTAX INTEGER (0..1)
                MAX-ACCESS read-write
                STATUS current
                DESCRIPTION
                        "Access to Current/Power Metering."
        ::= { userEntry 15 }

        userCallbackNum OBJECT-TYPE
                SYNTAX DisplayString(SIZE(0..32))
                MAX-ACCESS read-write
                STATUS current
                DESCRIPTION
                        "Callback number."
        ::= { userEntry 16 }

        userSubmit OBJECT-TYPE
                SYNTAX INTEGER (0..1)
                MAX-ACCESS read-write
                STATUS current
                DESCRIPTION
                        "Submit changes to user."
        ::= { userEntry 31 }

        --
        -- Environment Tables
        --

        environmentTables OBJECT IDENTIFIER ::= { wti 200 }

        environmentUnitTable OBJECT-TYPE
                SYNTAX SEQUENCE OF EnvironmentUnitEntry
                MAX-ACCESS not-accessible
                STATUS current
                DESCRIPTION
                        "A table of environment status for units."
        ::= { environmentTables 10 }

        environmentUnitEntry OBJECT-TYPE
                SYNTAX EnvironmentUnitEntry
                MAX-ACCESS not-accessible
                STATUS current
                DESCRIPTION
                        "Row definition for the environment unit table."
                INDEX { environmentUnitIndex }
        ::= { environmentUnitTable 1 }

        EnvironmentUnitEntry ::= SEQUENCE {
                environmentUnitIndex INTEGER,
                environmentUnitName DisplayString,
                environmentUnitTemperature INTEGER,
                environmentUnitCurrentA INTEGER,
                environmentUnitVoltageA INTEGER,
                environmentUnitPowerA INTEGER,
                environmentUnitCurrentB INTEGER,
                environmentUnitVoltageB INTEGER,
                environmentUnitPowerB INTEGER,
                environmentUnitCurrentC INTEGER,
                environmentUnitVoltageC INTEGER,
                environmentUnitPowerC INTEGER,
                environmentUnitCurrentD INTEGER,
                environmentUnitVoltageD INTEGER,
                environmentUnitPowerD INTEGER
        }

        environmentUnitIndex OBJECT-TYPE
                SYNTAX INTEGER (0..3)
                MAX-ACCESS not-accessible
                STATUS current
                DESCRIPTION
                        "Index for the environment unit table."
        ::= { environmentUnitEntry 1 }

        environmentUnitName OBJECT-TYPE
                SYNTAX DisplayString(SIZE(0..10))
                MAX-ACCESS read-only
                STATUS current
                DESCRIPTION
                        "The name of the unit."
        ::= { environmentUnitEntry 2 }

        environmentUnitTemperature OBJECT-TYPE
                SYNTAX INTEGER
                MAX-ACCESS read-only
                STATUS current
                DESCRIPTION
                        "The name of the unit."
        ::= { environmentUnitEntry 3 }

        environmentUnitCurrentA OBJECT-TYPE
                SYNTAX INTEGER
                MAX-ACCESS read-only
                STATUS current
                DESCRIPTION
                        "The number of amps in branch A for unit (In tenths of amps, divide by 10 for value in amps)."
        ::= { environmentUnitEntry 4 }

        environmentUnitVoltageA OBJECT-TYPE
                SYNTAX INTEGER
                MAX-ACCESS read-only
                STATUS current
                DESCRIPTION
                        "The voltage of branch A for unit."
        ::= { environmentUnitEntry 5 }

        environmentUnitPowerA OBJECT-TYPE
                SYNTAX INTEGER
                MAX-ACCESS read-only
                STATUS current
                DESCRIPTION
                        "The number of watts used by branch A for unit."
        ::= { environmentUnitEntry 6 }

        environmentUnitCurrentB OBJECT-TYPE
                SYNTAX INTEGER
                MAX-ACCESS read-only
                STATUS current
                DESCRIPTION
                        "The number of amps in branch B for unit (In tenths of amps, divide by 10 for value in amps)."
        ::= { environmentUnitEntry 7 }

        environmentUnitVoltageB OBJECT-TYPE
                SYNTAX INTEGER
                MAX-ACCESS read-only
                STATUS current
                DESCRIPTION
                        "The voltage of branch B for unit."
        ::= { environmentUnitEntry 8 }

        environmentUnitPowerB OBJECT-TYPE
                SYNTAX INTEGER
                MAX-ACCESS read-only
                STATUS current
                DESCRIPTION
                        "The number of watts used by branch b for unit."
        ::= { environmentUnitEntry 9 }

        environmentUnitCurrentC OBJECT-TYPE
                SYNTAX INTEGER
                MAX-ACCESS read-only
                STATUS current
                DESCRIPTION
                        "The number of amps in branch C for unit (In tenths of amps, divide by 10 for value in amps)."
        ::= { environmentUnitEntry 10 }

        environmentUnitVoltageC OBJECT-TYPE
                SYNTAX INTEGER
                MAX-ACCESS read-only
                STATUS current
                DESCRIPTION
                        "The voltage of branch C for unit."
        ::= { environmentUnitEntry 11 }

        environmentUnitPowerC OBJECT-TYPE
                SYNTAX INTEGER
                MAX-ACCESS read-only
                STATUS current
                DESCRIPTION
                        "The number of watts used by branch c for unit."
        ::= { environmentUnitEntry 12 }

        environmentUnitCurrentD OBJECT-TYPE
                SYNTAX INTEGER
                MAX-ACCESS read-only
                STATUS current
                DESCRIPTION
                        "The number of amps in branch D for unit (In tenths of amps, divide by 10 for value in amps)."
        ::= { environmentUnitEntry 13 }

        environmentUnitVoltageD OBJECT-TYPE
                SYNTAX INTEGER
                MAX-ACCESS read-only
                STATUS current
                DESCRIPTION
                        "The voltage of branch D for unit."
        ::= { environmentUnitEntry 14 }

        environmentUnitPowerD OBJECT-TYPE
                SYNTAX INTEGER
                MAX-ACCESS read-only
                STATUS current
                DESCRIPTION
                        "The number of watts used by branch d for unit."
        ::= { environmentUnitEntry 15 }

        environmentBranchATotalCurrent OBJECT-TYPE
                SYNTAX INTEGER
                MAX-ACCESS read-only
                STATUS current
                DESCRIPTION
                        "Total Current on BRANCH A (In tenths of amps, divide by 10 for value in amps)."
        ::= { environmentTables 20 }

        environmentBranchATotalPower OBJECT-TYPE
                SYNTAX INTEGER
                MAX-ACCESS read-only
                STATUS current
                DESCRIPTION
                        "Total Power on BRANCH A."
        ::= { environmentTables 30 }

        environmentBranchBTotalCurrent OBJECT-TYPE
                SYNTAX INTEGER
                MAX-ACCESS read-only
                STATUS current
                DESCRIPTION
                        "Total Current on BRANCH B (In tenths of amps, divide by 10 for value in amps)."
        ::= { environmentTables 40 }

        environmentBranchBTotalPower OBJECT-TYPE
                SYNTAX INTEGER
                MAX-ACCESS read-only
                STATUS current
                DESCRIPTION
                        "Total Power on BRANCH B."
        ::= { environmentTables 50 }

        environmentBranchCTotalCurrent OBJECT-TYPE
                SYNTAX INTEGER
                MAX-ACCESS read-only
                STATUS current
                DESCRIPTION
                        "Total Current on BRANCH C (In tenths of amps, divide by 10 for value in amps)."
        ::= { environmentTables 51 }

        environmentBranchCTotalPower OBJECT-TYPE
                SYNTAX INTEGER
                MAX-ACCESS read-only
                STATUS current
                DESCRIPTION
                        "Total Power on BRANCH C."
        ::= { environmentTables 52 }

        environmentBranchDTotalCurrent OBJECT-TYPE
                SYNTAX INTEGER
                MAX-ACCESS read-only
                STATUS current
                DESCRIPTION
                        "Total Current on BRANCH D (In tenths of amps, divide by 10 for value in amps)."
        ::= { environmentTables 53 }

        environmentBranchDTotalPower OBJECT-TYPE
                SYNTAX INTEGER
                MAX-ACCESS read-only
                STATUS current
                DESCRIPTION
                        "Total Power on BRANCH D."
        ::= { environmentTables 54 }

        environmentSystemTotalCurrent OBJECT-TYPE
                SYNTAX INTEGER
                MAX-ACCESS read-only
                STATUS current
                DESCRIPTION
                        "Total current for system  (In tenths of amps, divide by 10 for value in amps)."
        ::= { environmentTables 60 }

        environmentSystemTotalPower OBJECT-TYPE
                SYNTAX INTEGER
                MAX-ACCESS read-only
                STATUS current
                DESCRIPTION
                        "Total power on system."
        ::= { environmentTables 70 }

        environmentMonthlyPowerLog OBJECT-TYPE
                SYNTAX DisplayString
                MAX-ACCESS read-only
                STATUS current
                DESCRIPTION
                        "The monthly power usage log"
        ::= { environmentTables 80 }

        --
        -- Traps
        --

        wtiTraps OBJECT IDENTIFIER ::= { wti 300 }

        -- Trap Info

        trapInfo OBJECT-TYPE
                SYNTAX DisplayString
                MAX-ACCESS read-only
                STATUS current
                DESCRIPTION
                        "Alarm information"
        ::= { wtiTraps 1 }

        -- Test Traps

        testTraps OBJECT IDENTIFIER ::= { wtiTraps 2}

        testTrap TRAP-TYPE
                ENTERPRISE testTraps
                VARIABLES {
                trapInfo
                }
                DESCRIPTION
                        "A test trap"
        ::= 1

        -- Alarm Traps

        overCurrentInitialTraps OBJECT IDENTIFIER ::= { wtiTraps 4}

        overCurrentInitialSetTrap TRAP-TYPE
                ENTERPRISE overCurrentInitialTraps
                VARIABLES {
                trapInfo
                }
                DESCRIPTION
                        "Over Current Initial Alarm"
        ::= 1

        overCurrentInitialClearTrap TRAP-TYPE
                ENTERPRISE overCurrentInitialTraps
                VARIABLES {
                trapInfo
                }
                DESCRIPTION
                        "Over Current Initial Alarm (Clear)"
        ::= 2

        overCurrentCriticalTraps OBJECT IDENTIFIER ::= { wtiTraps 5}

        overCurrentCriticalSetTrap TRAP-TYPE
                ENTERPRISE overCurrentCriticalTraps
                VARIABLES {
                trapInfo
                }
                DESCRIPTION
                        "Over Current Critical Alarm"
        ::= 1

        overCurrentCriticalClearTrap TRAP-TYPE
                ENTERPRISE overCurrentCriticalTraps
                VARIABLES {
                trapInfo
                }
                DESCRIPTION
                        "Over Current Critical Alarm (Clear)"
        ::= 2

        overTemperatureInitialTraps OBJECT IDENTIFIER ::= { wtiTraps 6}

        overTemperatureInitialSetTrap TRAP-TYPE
                ENTERPRISE overTemperatureInitialTraps
                VARIABLES {
                trapInfo
                }
                DESCRIPTION
                        "Over Temperature Initial Alarm"
        ::= 1

        overTemperatureInitialClearTrap TRAP-TYPE
                ENTERPRISE overTemperatureInitialTraps
                VARIABLES {
                trapInfo
                }
                DESCRIPTION
                        "Over Temperature Initial Alarm (Clear)"
        ::= 2

        overTemperatureCriticalTraps OBJECT IDENTIFIER ::= { wtiTraps 7}

        overTemperatureCriticalSetTrap TRAP-TYPE
                ENTERPRISE overTemperatureCriticalTraps
                VARIABLES {
                trapInfo
                }
                DESCRIPTION
                        "Over Temperature Critical Alarm"
        ::= 1

        overTemperatureCriticalClearTrap TRAP-TYPE
                ENTERPRISE overTemperatureCriticalTraps
                VARIABLES {
                trapInfo
                }
                DESCRIPTION
                        "Over Temperature Critical Alarm (Clear)"
        ::= 2

        circuitBreakerOpenTraps OBJECT IDENTIFIER ::= { wtiTraps 8}

        circuitBreakerOpenSetTrap TRAP-TYPE
                ENTERPRISE circuitBreakerOpenTraps
                VARIABLES {
                trapInfo
                }
                DESCRIPTION
                        "Circuit Breaker Open Alarm"
        ::= 1

        circuitBreakerOpenClearTrap TRAP-TYPE
                ENTERPRISE circuitBreakerOpenTraps
                VARIABLES {
                trapInfo
                }
                DESCRIPTION
                        "Circuit Breaker Open Alarm (Clear)"
        ::= 2

        lostCommTraps OBJECT IDENTIFIER ::= { wtiTraps 9}

        lostCommSetTrap TRAP-TYPE
                ENTERPRISE lostCommTraps
                VARIABLES {
                trapInfo
                }
                DESCRIPTION
                        "Lost Communication with AUX Unit"
        ::= 1

        lostCommClearTrap TRAP-TYPE
                ENTERPRISE lostCommTraps
                VARIABLES {
                trapInfo
                }
                DESCRIPTION
                        "Lost Communication with AUX Unit (Clear)"
        ::= 2

        lostVoltageTraps OBJECT IDENTIFIER ::= { wtiTraps 10}

        lostVoltageSetTrap TRAP-TYPE
                ENTERPRISE lostVoltageTraps
                VARIABLES {
                trapInfo
                }
                DESCRIPTION
                        "Lost Voltage (Line In)"
        ::= 1

        lostVoltageClearTrap TRAP-TYPE
                ENTERPRISE lostVoltageTraps
                VARIABLES {
                trapInfo
                }
                DESCRIPTION
                        "Lost Voltage (Line In) (Clear)"
        ::= 2

        pingNoAnswerTraps OBJECT IDENTIFIER ::= { wtiTraps 11}

        pingNoAnswerSetTrap TRAP-TYPE
                ENTERPRISE pingNoAnswerTraps
                VARIABLES {
                trapInfo
                }
                DESCRIPTION
                        "Ping No Answer"
        ::= 1

        pingNoAnswerClearTrap TRAP-TYPE
                ENTERPRISE pingNoAnswerTraps
                VARIABLES {
                trapInfo
                }
                DESCRIPTION
                        "Ping No Answer (Clear)"
        ::= 2

        lockoutTraps OBJECT IDENTIFIER ::= { wtiTraps 12}

        lockoutSetTrap TRAP-TYPE
                ENTERPRISE lockoutTraps
                VARIABLES {
                trapInfo
                }
                DESCRIPTION
                        "Invalid Access Lockout"
        ::= 1

        lockoutClearTrap TRAP-TYPE
                ENTERPRISE lockoutTraps
                VARIABLES {
                trapInfo
                }
                DESCRIPTION
                        "Invalid Access Lockout (Clear)"
        ::= 2

        powercycleTraps OBJECT IDENTIFIER ::= { wtiTraps 13}

        powercycleSetTrap TRAP-TYPE
                ENTERPRISE powercycleTraps
                VARIABLES {
                trapInfo
                }
                DESCRIPTION
                        "Power Cycle"
        ::= 1

 END
