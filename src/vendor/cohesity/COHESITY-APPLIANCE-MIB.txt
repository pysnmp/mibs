-- *****************************************************************
-- Cohesity Secondary Storage Appliance MIB
--
-- DO NOT EDIT THIS FILE MANUALLY. IT IS AUTOMATICALLY GENERATED BY
-- COHESITY MIB GENERATOR.
--
-- Copyright (c) 2017-2022 by Cohesity, Inc.
--
-- All rights reserved.
--
-- *****************************************************************
--
-- Top-level infrastructure of the Cohesity Appliance enterprise MIB tree.
--
COHESITY-APPLIANCE-MIB DEFINITIONS ::= BEGIN

-- *****************************************************************
--
-- IMPORTS section
--
-- *****************************************************************
IMPORTS
  MODULE-IDENTITY, OBJECT-TYPE, NOTIFICATION-TYPE, enterprises, Integer32, Gauge32, Counter32, Counter64, TimeTicks, IpAddress, Opaque FROM SNMPv2-SMI
  PhysAddress, DisplayString, TEXTUAL-CONVENTION FROM SNMPv2-TC
  IANAifType FROM IANAifType-MIB
  MODULE-COMPLIANCE, OBJECT-GROUP, NOTIFICATION-GROUP FROM SNMPv2-CONF
;

-- *****************************************************************
--
-- MODULE IDENTITY AND REVISION GROUP
--
-- *****************************************************************

cohesityApplianceMIB  MODULE-IDENTITY
  LAST-UPDATED "202409270532Z" -- UTC format is YYMMDDHHmmZ
  ORGANIZATION "Cohesity Inc."
  CONTACT-INFO "Cohesity support, support@cohesity.com"
  DESCRIPTION
    "Cohesity OS enterprise-specific MIB tree."
    REVISION "202409270532Z"
    DESCRIPTION "Initial draft 0.2"
  ::= { enterprises 47421 }

-- *****************************************************************
--
-- OBJECT IDENTIFIER definition section
--
-- *****************************************************************

caNotifsGroup  OBJECT IDENTIFIER ::= { cohesityApplianceMIB 0 }

caEventVariables  OBJECT IDENTIFIER ::= { cohesityApplianceMIB 1 }

cohesityApplianceMIBConformance  OBJECT IDENTIFIER ::= { cohesityApplianceMIB 2 }

caSysInfoGroup  OBJECT IDENTIFIER ::= { cohesityApplianceMIB 3 }

caSysInfoClusterGroup  OBJECT IDENTIFIER ::= { caSysInfoGroup 100 }

caSysInfoChassisGroup  OBJECT IDENTIFIER ::= { caSysInfoGroup 200 }

caSysInfoPowerSupplyGroup  OBJECT IDENTIFIER ::= { caSysInfoGroup 300 }

caSysInfoFanGroup  OBJECT IDENTIFIER ::= { caSysInfoGroup 400 }

caSysInfoNodeGroup  OBJECT IDENTIFIER ::= { caSysInfoGroup 500 }

caSysInfoProcessorGroup  OBJECT IDENTIFIER ::= { caSysInfoGroup 600 }

caSysInfoMemoryGroup  OBJECT IDENTIFIER ::= { caSysInfoGroup 700 }

caSysInfoDiskGroup  OBJECT IDENTIFIER ::= { caSysInfoGroup 800 }

caSysInfoInterfaceGroup  OBJECT IDENTIFIER ::= { caSysInfoGroup 900 }

caSysInfoMiscGroup  OBJECT IDENTIFIER ::= { caSysInfoGroup 1000 }

caSysStatsGroup  OBJECT IDENTIFIER ::= { cohesityApplianceMIB 4 }

-- *****************************************************************
--
-- Cohesity Appliance enterprise-specific management objects group.
--
-- OBJECT Group definition section
--
-- *****************************************************************

clusterName OBJECT-TYPE
  SYNTAX DisplayString
  MAX-ACCESS read-only
  STATUS current
  DESCRIPTION
    "Cluster's Name."
  ::= { caSysInfoClusterGroup 1 }

clusterId OBJECT-TYPE
  SYNTAX DisplayString
  MAX-ACCESS read-only
  STATUS current
  DESCRIPTION
    "Cluster's ID."
  ::= { caSysInfoClusterGroup 2 }

clusterSoftwareVersion OBJECT-TYPE
  SYNTAX DisplayString
  MAX-ACCESS read-only
  STATUS current
  DESCRIPTION
    "Cluster's Software Version."
  ::= { caSysInfoClusterGroup 3 }

clusterNodeCount OBJECT-TYPE
  SYNTAX DisplayString
  MAX-ACCESS read-only
  STATUS current
  DESCRIPTION
    "Cluster's Node Count."
  ::= { caSysInfoClusterGroup 4 }

clusterState OBJECT-TYPE
  SYNTAX DisplayString
  MAX-ACCESS read-only
  STATUS current
  DESCRIPTION
    "Cluster's State."
  ::= { caSysInfoClusterGroup 5 }

clusterCreateTime OBJECT-TYPE
  SYNTAX DisplayString
  MAX-ACCESS read-only
  STATUS current
  DESCRIPTION
    "Cluster's CreateTime."
  ::= { caSysInfoClusterGroup 6 }

clusterCapacity OBJECT-TYPE
  SYNTAX DisplayString
  MAX-ACCESS read-only
  STATUS current
  DESCRIPTION
    "Cluster's Capacity."
  ::= { caSysInfoClusterGroup 7 }

clusterUsage OBJECT-TYPE
  SYNTAX DisplayString
  MAX-ACCESS read-only
  STATUS current
  DESCRIPTION
    "Cluster's Usage."
  ::= { caSysInfoClusterGroup 8 }

chassisProduct OBJECT-TYPE
  SYNTAX DisplayString
  MAX-ACCESS read-only
  STATUS current
  DESCRIPTION
    "Chassis's Product."
  ::= { caSysInfoChassisGroup 1 }

chassisVendor OBJECT-TYPE
  SYNTAX DisplayString
  MAX-ACCESS read-only
  STATUS current
  DESCRIPTION
    "Chassis's Vendor."
  ::= { caSysInfoChassisGroup 2 }

chassisSerial OBJECT-TYPE
  SYNTAX DisplayString
  MAX-ACCESS read-only
  STATUS current
  DESCRIPTION
    "Chassis's Serial."
  ::= { caSysInfoChassisGroup 3 }

nodeSlot OBJECT-TYPE
  SYNTAX DisplayString
  MAX-ACCESS read-only
  STATUS current
  DESCRIPTION
    "Node's Slot."
  ::= { caSysInfoNodeGroup 1 }

nodeModel OBJECT-TYPE
  SYNTAX DisplayString
  MAX-ACCESS read-only
  STATUS current
  DESCRIPTION
    "Node's Model."
  ::= { caSysInfoNodeGroup 2 }

nodeVendor OBJECT-TYPE
  SYNTAX DisplayString
  MAX-ACCESS read-only
  STATUS current
  DESCRIPTION
    "Node's Vendor."
  ::= { caSysInfoNodeGroup 3 }

nodeBios OBJECT-TYPE
  SYNTAX DisplayString
  MAX-ACCESS read-only
  STATUS current
  DESCRIPTION
    "Node's Bios."
  ::= { caSysInfoNodeGroup 4 }

nodeID OBJECT-TYPE
  SYNTAX DisplayString
  MAX-ACCESS read-only
  STATUS current
  DESCRIPTION
    "Node's ID."
  ::= { caSysInfoNodeGroup 5 }

nodeIp OBJECT-TYPE
  SYNTAX DisplayString
  MAX-ACCESS read-only
  STATUS current
  DESCRIPTION
    "Node's IP."
  ::= { caSysInfoNodeGroup 6 }

nodeSoftwareVersion OBJECT-TYPE
  SYNTAX DisplayString
  MAX-ACCESS read-only
  STATUS current
  DESCRIPTION
    "Node's Software Version."
  ::= { caSysInfoNodeGroup 7 }

nodeUptime OBJECT-TYPE
  SYNTAX DisplayString
  MAX-ACCESS read-only
  STATUS current
  DESCRIPTION
    "Node's Uptime."
  ::= { caSysInfoNodeGroup 8 }

cohesityNodeSerial OBJECT-TYPE
  SYNTAX DisplayString
  MAX-ACCESS read-only
  STATUS current
  DESCRIPTION
    "Cohesity Node's Serial Number."
  ::= { caSysInfoNodeGroup 9 }

nodeIpmiIp OBJECT-TYPE
  SYNTAX DisplayString
  MAX-ACCESS read-only
  STATUS current
  DESCRIPTION
    "Node's IPMI IP."
  ::= { caSysInfoNodeGroup 10 }

miscInteger32 OBJECT-TYPE
  SYNTAX Integer32
  MAX-ACCESS read-only
  STATUS current
  DESCRIPTION
    "Testing integer."
  ::= { caSysInfoMiscGroup 1 }

miscOctetString OBJECT-TYPE
  SYNTAX DisplayString
  MAX-ACCESS read-only
  STATUS current
  DESCRIPTION
    "Testing Octet String."
  ::= { caSysInfoMiscGroup 2 }

miscNull OBJECT-TYPE
  SYNTAX DisplayString
  MAX-ACCESS read-only
  STATUS current
  DESCRIPTION
    "Testing Null."
  ::= { caSysInfoMiscGroup 3 }

miscObjectId OBJECT-TYPE
  SYNTAX DisplayString
  MAX-ACCESS read-only
  STATUS current
  DESCRIPTION
    "Testing Object Identifier."
  ::= { caSysInfoMiscGroup 4 }

miscCounter32 OBJECT-TYPE
  SYNTAX Counter32
  MAX-ACCESS read-only
  STATUS current
  DESCRIPTION
    "Testing Counter32r."
  ::= { caSysInfoMiscGroup 5 }

miscIPAddress OBJECT-TYPE
  SYNTAX IpAddress
  MAX-ACCESS read-only
  STATUS current
  DESCRIPTION
    "Testing IP Address."
  ::= { caSysInfoMiscGroup 6 }

miscGauge32 OBJECT-TYPE
  SYNTAX Gauge32
  MAX-ACCESS read-only
  STATUS current
  DESCRIPTION
    "Testing Gauge32."
  ::= { caSysInfoMiscGroup 7 }

miscTimeTicks OBJECT-TYPE
  SYNTAX TimeTicks
  MAX-ACCESS read-only
  STATUS current
  DESCRIPTION
    "Testing TimeTicks."
  ::= { caSysInfoMiscGroup 8 }

miscOpaque OBJECT-TYPE
  SYNTAX Opaque
  MAX-ACCESS read-only
  STATUS current
  DESCRIPTION
    "Testing Opaque."
  ::= { caSysInfoMiscGroup 9 }

miscCounter64 OBJECT-TYPE
  SYNTAX Counter64
  MAX-ACCESS read-only
  STATUS current
  DESCRIPTION
    "Testing Counter64."
  ::= { caSysInfoMiscGroup 10 }

-- *****************************************************************
--
-- Cohesity Appliance enterprise-specific management objects.
--
-- OBJECT TABLE definition section
--
-- *****************************************************************

powerSupplyInfoTable OBJECT-TYPE    -- the table object
  SYNTAX SEQUENCE OF PowerSupplyInfoEntry
  MAX-ACCESS not-accessible
  STATUS current
  DESCRIPTION
    "Power supply information table."
  ::= { caSysInfoPowerSupplyGroup 1 }

powerSupplyInfoEntry OBJECT-TYPE    -- the entry object
  SYNTAX PowerSupplyInfoEntry
  MAX-ACCESS not-accessible
  STATUS current
  DESCRIPTION
    "Power supply information table."
  INDEX { psSlot }
  ::= { powerSupplyInfoTable 1 }

PowerSupplyInfoEntry ::=          -- the SEQUENCE statement
  SEQUENCE {
    psSlot    DisplayString,
    psWatts    DisplayString,
    psState    DisplayString
}

psSlot OBJECT-TYPE
  SYNTAX DisplayString
  MAX-ACCESS read-only
  STATUS current
  DESCRIPTION
    "Power supply slot."
  ::= { powerSupplyInfoEntry 1 }

psWatts OBJECT-TYPE
  SYNTAX DisplayString
  MAX-ACCESS read-only
  STATUS current
  DESCRIPTION
    "Power supply Output Watts."
  ::= { powerSupplyInfoEntry 2 }

psState OBJECT-TYPE
  SYNTAX DisplayString
  MAX-ACCESS read-only
  STATUS current
  DESCRIPTION
    "Power supply state."
  ::= { powerSupplyInfoEntry 3 }

fanInfoTable OBJECT-TYPE    -- the table object
  SYNTAX SEQUENCE OF FanInfoEntry
  MAX-ACCESS not-accessible
  STATUS current
  DESCRIPTION
    "Fan information table."
  ::= { caSysInfoFanGroup 1 }

fanInfoEntry OBJECT-TYPE    -- the entry object
  SYNTAX FanInfoEntry
  MAX-ACCESS not-accessible
  STATUS current
  DESCRIPTION
    "Fan information table."
  INDEX { fanSlot }
  ::= { fanInfoTable 1 }

FanInfoEntry ::=          -- the SEQUENCE statement
  SEQUENCE {
    fanSlot    DisplayString,
    fanRpm    DisplayString,
    fanState    DisplayString
}

fanSlot OBJECT-TYPE
  SYNTAX DisplayString
  MAX-ACCESS read-only
  STATUS current
  DESCRIPTION
    "FAN slot."
  ::= { fanInfoEntry 1 }

fanRpm OBJECT-TYPE
  SYNTAX DisplayString
  MAX-ACCESS read-only
  STATUS current
  DESCRIPTION
    "FAN RPm."
  ::= { fanInfoEntry 2 }

fanState OBJECT-TYPE
  SYNTAX DisplayString
  MAX-ACCESS read-only
  STATUS current
  DESCRIPTION
    "FAN state."
  ::= { fanInfoEntry 3 }

memInfoTable OBJECT-TYPE    -- the table object
  SYNTAX SEQUENCE OF MemInfoEntry
  MAX-ACCESS not-accessible
  STATUS current
  DESCRIPTION
    "DIMM's information table."
  ::= { caSysInfoMemoryGroup 1 }

memInfoEntry OBJECT-TYPE    -- the entry object
  SYNTAX MemInfoEntry
  MAX-ACCESS not-accessible
  STATUS current
  DESCRIPTION
    "DIMM's information table."
  INDEX { memSlot }
  ::= { memInfoTable 1 }

MemInfoEntry ::=          -- the SEQUENCE statement
  SEQUENCE {
    memSlot    DisplayString,
    memVendor    DisplayString,
    memSize    DisplayString,
    memSpeed    DisplayString,
    memState    DisplayString
}

memSlot OBJECT-TYPE
  SYNTAX DisplayString
  MAX-ACCESS read-only
  STATUS current
  DESCRIPTION
    "DIMM's Slot."
  ::= { memInfoEntry 1 }

memVendor OBJECT-TYPE
  SYNTAX DisplayString
  MAX-ACCESS read-only
  STATUS current
  DESCRIPTION
    "DIMM's Vendor."
  ::= { memInfoEntry 2 }

memSize OBJECT-TYPE
  SYNTAX DisplayString
  MAX-ACCESS read-only
  STATUS current
  DESCRIPTION
    "DIMM's Size."
  ::= { memInfoEntry 3 }

memSpeed OBJECT-TYPE
  SYNTAX DisplayString
  MAX-ACCESS read-only
  STATUS current
  DESCRIPTION
    "DIMM's Speed."
  ::= { memInfoEntry 4 }

memState OBJECT-TYPE
  SYNTAX DisplayString
  MAX-ACCESS read-only
  STATUS current
  DESCRIPTION
    "DIMM's State."
  ::= { memInfoEntry 5 }

cpuInfoTable OBJECT-TYPE    -- the table object
  SYNTAX SEQUENCE OF CpuInfoEntry
  MAX-ACCESS not-accessible
  STATUS current
  DESCRIPTION
    "Processor's information table."
  ::= { caSysInfoProcessorGroup 1 }

cpuInfoEntry OBJECT-TYPE    -- the entry object
  SYNTAX CpuInfoEntry
  MAX-ACCESS not-accessible
  STATUS current
  DESCRIPTION
    "Processor's information table."
  INDEX { cpuSlot }
  ::= { cpuInfoTable 1 }

CpuInfoEntry ::=          -- the SEQUENCE statement
  SEQUENCE {
    cpuSlot    DisplayString,
    cpuVendor    DisplayString,
    cpuVersion    DisplayString,
    cpuSpeed    DisplayString,
    cpuCoreCount    DisplayString,
    cpudState    DisplayString
}

cpuSlot OBJECT-TYPE
  SYNTAX DisplayString
  MAX-ACCESS read-only
  STATUS current
  DESCRIPTION
    "CPU's Slot."
  ::= { cpuInfoEntry 1 }

cpuVendor OBJECT-TYPE
  SYNTAX DisplayString
  MAX-ACCESS read-only
  STATUS current
  DESCRIPTION
    "CPU's Vendor."
  ::= { cpuInfoEntry 2 }

cpuVersion OBJECT-TYPE
  SYNTAX DisplayString
  MAX-ACCESS read-only
  STATUS current
  DESCRIPTION
    "CPU's Version."
  ::= { cpuInfoEntry 3 }

cpuSpeed OBJECT-TYPE
  SYNTAX DisplayString
  MAX-ACCESS read-only
  STATUS current
  DESCRIPTION
    "Cpu's Speed."
  ::= { cpuInfoEntry 4 }

cpuCoreCount OBJECT-TYPE
  SYNTAX DisplayString
  MAX-ACCESS read-only
  STATUS current
  DESCRIPTION
    "Cpu's Core Count."
  ::= { cpuInfoEntry 5 }

cpudState OBJECT-TYPE
  SYNTAX DisplayString
  MAX-ACCESS read-only
  STATUS current
  DESCRIPTION
    "CPU's State."
  ::= { cpuInfoEntry 6 }

diskInfoTable OBJECT-TYPE    -- the table object
  SYNTAX SEQUENCE OF DiskInfoEntry
  MAX-ACCESS not-accessible
  STATUS current
  DESCRIPTION
    "Disk information table."
  ::= { caSysInfoDiskGroup 1 }

diskInfoEntry OBJECT-TYPE    -- the entry object
  SYNTAX DiskInfoEntry
  MAX-ACCESS not-accessible
  STATUS current
  DESCRIPTION
    "Disk information table."
  INDEX { diskSlot }
  ::= { diskInfoTable 1 }

DiskInfoEntry ::=          -- the SEQUENCE statement
  SEQUENCE {
    diskSlot    DisplayString,
    diskVendor    DisplayString,
    diskModel    DisplayString,
    diskSerial    DisplayString,
    diskFirmware    DisplayString,
    diskCapacity    DisplayString,
    diskUsage    DisplayString,
    diskState    DisplayString
}

diskSlot OBJECT-TYPE
  SYNTAX DisplayString
  MAX-ACCESS read-only
  STATUS current
  DESCRIPTION
    "Disk slot."
  ::= { diskInfoEntry 1 }

diskVendor OBJECT-TYPE
  SYNTAX DisplayString
  MAX-ACCESS read-only
  STATUS current
  DESCRIPTION
    "Disk Vendor."
  ::= { diskInfoEntry 2 }

diskModel OBJECT-TYPE
  SYNTAX DisplayString
  MAX-ACCESS read-only
  STATUS current
  DESCRIPTION
    "Disk's Model."
  ::= { diskInfoEntry 3 }

diskSerial OBJECT-TYPE
  SYNTAX DisplayString
  MAX-ACCESS read-only
  STATUS current
  DESCRIPTION
    "Disk's Serial."
  ::= { diskInfoEntry 4 }

diskFirmware OBJECT-TYPE
  SYNTAX DisplayString
  MAX-ACCESS read-only
  STATUS current
  DESCRIPTION
    "Disk's Firmware."
  ::= { diskInfoEntry 5 }

diskCapacity OBJECT-TYPE
  SYNTAX DisplayString
  MAX-ACCESS read-only
  STATUS current
  DESCRIPTION
    "Disk's Capacity."
  ::= { diskInfoEntry 6 }

diskUsage OBJECT-TYPE
  SYNTAX DisplayString
  MAX-ACCESS read-only
  STATUS current
  DESCRIPTION
    "Disk's Usage."
  ::= { diskInfoEntry 7 }

diskState OBJECT-TYPE
  SYNTAX DisplayString
  MAX-ACCESS read-only
  STATUS current
  DESCRIPTION
    "Disk's State."
  ::= { diskInfoEntry 8 }

ifInfoTable OBJECT-TYPE    -- the table object
  SYNTAX SEQUENCE OF IfInfoEntry
  MAX-ACCESS not-accessible
  STATUS current
  DESCRIPTION
    "Interface information table."
  ::= { caSysInfoInterfaceGroup 1 }

ifInfoEntry OBJECT-TYPE    -- the entry object
  SYNTAX IfInfoEntry
  MAX-ACCESS not-accessible
  STATUS current
  DESCRIPTION
    "Interface information table."
  INDEX { ifIndex }
  ::= { ifInfoTable 1 }

IfInfoEntry ::=          -- the SEQUENCE statement
  SEQUENCE {
    ifIndex    INTEGER,
    ifDescr    DisplayString,
    ifType    DisplayString,
    ifMtu    Integer32,
    ifSpeed    Gauge32,
    ifPhysAddress    PhysAddress,
    ifAdminStatus    DisplayString,
    ifLastChange    TimeTicks,
    ifInOctets    Counter32,
    ifInErrors    Counter32,
    ifOutOctets    Counter32,
    ifOutErrors    Counter32,
    ifState    DisplayString
}

ifIndex OBJECT-TYPE
  SYNTAX INTEGER
  MAX-ACCESS read-only
  STATUS current
  DESCRIPTION
    "Interface Index."
  ::= { ifInfoEntry 1 }

ifDescr OBJECT-TYPE
  SYNTAX DisplayString
  MAX-ACCESS read-only
  STATUS current
  DESCRIPTION
    "Interface Description."
  ::= { ifInfoEntry 2 }

ifType OBJECT-TYPE
  SYNTAX DisplayString
  MAX-ACCESS read-only
  STATUS current
  DESCRIPTION
    "Interface Type."
  ::= { ifInfoEntry 3 }

ifMtu OBJECT-TYPE
  SYNTAX Integer32
  MAX-ACCESS read-only
  STATUS current
  DESCRIPTION
    "Interface's MTU."
  ::= { ifInfoEntry 4 }

ifSpeed OBJECT-TYPE
  SYNTAX Gauge32
  MAX-ACCESS read-only
  STATUS current
  DESCRIPTION
    "Interface's Speed."
  ::= { ifInfoEntry 5 }

ifPhysAddress OBJECT-TYPE
  SYNTAX PhysAddress
  MAX-ACCESS read-only
  STATUS current
  DESCRIPTION
    "Interface Physical address."
  ::= { ifInfoEntry 6 }

ifAdminStatus OBJECT-TYPE
  SYNTAX DisplayString
  MAX-ACCESS read-only
  STATUS current
  DESCRIPTION
    "Interface's admin status."
  ::= { ifInfoEntry 7 }

ifLastChange OBJECT-TYPE
  SYNTAX TimeTicks
  MAX-ACCESS read-only
  STATUS current
  DESCRIPTION
    "Interface's last change."
  ::= { ifInfoEntry 8 }

ifInOctets OBJECT-TYPE
  SYNTAX Counter32
  MAX-ACCESS read-only
  STATUS current
  DESCRIPTION
    "Interface's incoming packets."
  ::= { ifInfoEntry 9 }

ifInErrors OBJECT-TYPE
  SYNTAX Counter32
  MAX-ACCESS read-only
  STATUS current
  DESCRIPTION
    "Interface's incoming packets errors."
  ::= { ifInfoEntry 10 }

ifOutOctets OBJECT-TYPE
  SYNTAX Counter32
  MAX-ACCESS read-only
  STATUS current
  DESCRIPTION
    "Interface's sending packets."
  ::= { ifInfoEntry 11 }

ifOutErrors OBJECT-TYPE
  SYNTAX Counter32
  MAX-ACCESS read-only
  STATUS current
  DESCRIPTION
    "Interface's sending packets errors."
  ::= { ifInfoEntry 12 }

ifState OBJECT-TYPE
  SYNTAX DisplayString
  MAX-ACCESS read-only
  STATUS current
  DESCRIPTION
    "Interface's state."
  ::= { ifInfoEntry 13 }

-- *****************************************************************
--
-- Cohesity Appliance enterprise-specific management objects.
--
-- OBJECT TYPE definition section
--
-- *****************************************************************

diskNotHealthyEvent OBJECT-TYPE
  SYNTAX OCTET STRING (SIZE(0..1000))
  MAX-ACCESS read-only
  STATUS current
  DESCRIPTION
    "Disk is not healthy."
  ::= { caEventVariables 1 }

nodePingFailedEvent OBJECT-TYPE
  SYNTAX OCTET STRING (SIZE(0..1000))
  MAX-ACCESS read-only
  STATUS current
  DESCRIPTION
    "Node is not pingable."
  ::= { caEventVariables 2 }

markDiskForRemovalEvent OBJECT-TYPE
  SYNTAX OCTET STRING (SIZE(0..1000))
  MAX-ACCESS read-only
  STATUS current
  DESCRIPTION
    "Disk is marked for removal."
  ::= { caEventVariables 3 }

upgradeFailedEvent OBJECT-TYPE
  SYNTAX OCTET STRING (SIZE(0..1000))
  MAX-ACCESS read-only
  STATUS current
  DESCRIPTION
    "Node failed to upgrade."
  ::= { caEventVariables 4 }

newDiskFoundEvent OBJECT-TYPE
  SYNTAX OCTET STRING (SIZE(0..1000))
  MAX-ACCESS read-only
  STATUS current
  DESCRIPTION
    "New disk is found."
  ::= { caEventVariables 5 }

diskSpaceLowEvent OBJECT-TYPE
  SYNTAX OCTET STRING (SIZE(0..1000))
  MAX-ACCESS read-only
  STATUS current
  DESCRIPTION
    "Disk free space is low."
  ::= { caEventVariables 6 }

timeServiceEvent OBJECT-TYPE
  SYNTAX OCTET STRING (SIZE(0..1000))
  MAX-ACCESS read-only
  STATUS current
  DESCRIPTION
    "Node can not sync time."
  ::= { caEventVariables 7 }

missingDiskEvent OBJECT-TYPE
  SYNTAX OCTET STRING (SIZE(0..1000))
  MAX-ACCESS read-only
  STATUS current
  DESCRIPTION
    "One or more disks are missing."
  ::= { caEventVariables 8 }

writeLimitEvent OBJECT-TYPE
  SYNTAX OCTET STRING (SIZE(0..1000))
  MAX-ACCESS read-only
  STATUS current
  DESCRIPTION
    "SSD is reaching its write limit."
  ::= { caEventVariables 9 }

memUncorrectableEccEvent OBJECT-TYPE
  SYNTAX OCTET STRING (SIZE(0..1000))
  MAX-ACCESS read-only
  STATUS current
  DESCRIPTION
    "Memory found uncorrectable ECC."
  ::= { caEventVariables 10 }

watchdogTriggeredEvent OBJECT-TYPE
  SYNTAX OCTET STRING (SIZE(0..1000))
  MAX-ACCESS read-only
  STATUS current
  DESCRIPTION
    "IPMI watchdog triggered."
  ::= { caEventVariables 12 }

tempOutOfHighRangeEvent OBJECT-TYPE
  SYNTAX OCTET STRING (SIZE(0..1000))
  MAX-ACCESS read-only
  STATUS current
  DESCRIPTION
    "Temperature Sensor Out of High Range."
  ::= { caEventVariables 13 }

tempOutOfLowRangeEvent OBJECT-TYPE
  SYNTAX OCTET STRING (SIZE(0..1000))
  MAX-ACCESS read-only
  STATUS current
  DESCRIPTION
    "Temperature Sensor Out of Low Range."
  ::= { caEventVariables 14 }

voltOutOfHighRangeEvent OBJECT-TYPE
  SYNTAX OCTET STRING (SIZE(0..1000))
  MAX-ACCESS read-only
  STATUS current
  DESCRIPTION
    "Voltage Sensor Out of High Range."
  ::= { caEventVariables 15 }

voltOutOfLowRangeEvent OBJECT-TYPE
  SYNTAX OCTET STRING (SIZE(0..1000))
  MAX-ACCESS read-only
  STATUS current
  DESCRIPTION
    "Voltage Sensor Out of Low Range."
  ::= { caEventVariables 16 }

driveRemovedEvent OBJECT-TYPE
  SYNTAX OCTET STRING (SIZE(0..1000))
  MAX-ACCESS read-only
  STATUS current
  DESCRIPTION
    "Drive is removed."
  ::= { caEventVariables 17 }

drivePresentEvent OBJECT-TYPE
  SYNTAX OCTET STRING (SIZE(0..1000))
  MAX-ACCESS read-only
  STATUS current
  DESCRIPTION
    "Drive is present."
  ::= { caEventVariables 18 }

driveFaultEvent OBJECT-TYPE
  SYNTAX OCTET STRING (SIZE(0..1000))
  MAX-ACCESS read-only
  STATUS current
  DESCRIPTION
    "Drive is faulty."
  ::= { caEventVariables 19 }

powerSupplyRemovedEvent OBJECT-TYPE
  SYNTAX OCTET STRING (SIZE(0..1000))
  MAX-ACCESS read-only
  STATUS current
  DESCRIPTION
    "Power supply is removed."
  ::= { caEventVariables 20 }

powerSupplyInsertedEvent OBJECT-TYPE
  SYNTAX OCTET STRING (SIZE(0..1000))
  MAX-ACCESS read-only
  STATUS current
  DESCRIPTION
    "Power supply is inserted."
  ::= { caEventVariables 21 }

linkIsDownEvent OBJECT-TYPE
  SYNTAX OCTET STRING (SIZE(0..1000))
  MAX-ACCESS read-only
  STATUS current
  DESCRIPTION
    "Interface is down."
  ::= { caEventVariables 22 }

linkIsUpEvent OBJECT-TYPE
  SYNTAX OCTET STRING (SIZE(0..1000))
  MAX-ACCESS read-only
  STATUS current
  DESCRIPTION
    "Interface is up."
  ::= { caEventVariables 23 }

ipmiSelClearedEvent OBJECT-TYPE
  SYNTAX OCTET STRING (SIZE(0..1000))
  MAX-ACCESS read-only
  STATUS current
  DESCRIPTION
    "IPMI SEL log cleared."
  ::= { caEventVariables 24 }

nodeRebootedEvent OBJECT-TYPE
  SYNTAX OCTET STRING (SIZE(0..1000))
  MAX-ACCESS read-only
  STATUS current
  DESCRIPTION
    "Node rebooted."
  ::= { caEventVariables 25 }

thermalTripTriggeredEvent OBJECT-TYPE
  SYNTAX OCTET STRING (SIZE(0..1000))
  MAX-ACCESS read-only
  STATUS current
  DESCRIPTION
    "Thermal Trip Triggered."
  ::= { caEventVariables 26 }

powerSupplyAcLostEvent OBJECT-TYPE
  SYNTAX OCTET STRING (SIZE(0..1000))
  MAX-ACCESS read-only
  STATUS current
  DESCRIPTION
    "Power supply AC lost."
  ::= { caEventVariables 27 }

nodeChassisChangedEvent OBJECT-TYPE
  SYNTAX OCTET STRING (SIZE(0..1000))
  MAX-ACCESS read-only
  STATUS current
  DESCRIPTION
    "Chassis is changed."
  ::= { caEventVariables 28 }

raidDegradedEvent OBJECT-TYPE
  SYNTAX OCTET STRING (SIZE(0..1000))
  MAX-ACCESS read-only
  STATUS current
  DESCRIPTION
    "RAID is degraded."
  ::= { caEventVariables 29 }

diskAddedToClusterEvent OBJECT-TYPE
  SYNTAX OCTET STRING (SIZE(0..1000))
  MAX-ACCESS read-only
  STATUS current
  DESCRIPTION
    "Disk is added to cluster and ready for use."
  ::= { caEventVariables 30 }

systemLedAmberEvent OBJECT-TYPE
  SYNTAX OCTET STRING (SIZE(0..1000))
  MAX-ACCESS read-only
  STATUS current
  DESCRIPTION
    "System amber LED is on."
  ::= { caEventVariables 31 }

cpuThrottledEvent OBJECT-TYPE
  SYNTAX OCTET STRING (SIZE(0..1000))
  MAX-ACCESS read-only
  STATUS current
  DESCRIPTION
    "CPU is throttled."
  ::= { caEventVariables 32 }

fanRemovedEvent OBJECT-TYPE
  SYNTAX OCTET STRING (SIZE(0..1000))
  MAX-ACCESS read-only
  STATUS current
  DESCRIPTION
    "Fan is removed."
  ::= { caEventVariables 33 }

fanInsertedEvent OBJECT-TYPE
  SYNTAX OCTET STRING (SIZE(0..1000))
  MAX-ACCESS read-only
  STATUS current
  DESCRIPTION
    "Fan is inserted."
  ::= { caEventVariables 34 }

fanSpeedOutOfLowRangeEvent OBJECT-TYPE
  SYNTAX OCTET STRING (SIZE(0..1000))
  MAX-ACCESS read-only
  STATUS current
  DESCRIPTION
    "Fan Speed Out of Low Range."
  ::= { caEventVariables 35 }

chassisDownEvent OBJECT-TYPE
  SYNTAX OCTET STRING (SIZE(0..1000))
  MAX-ACCESS read-only
  STATUS current
  DESCRIPTION
    "All nodes in the chassis are unreachable."
  ::= { caEventVariables 36 }

ipmiUnreachableEvent OBJECT-TYPE
  SYNTAX OCTET STRING (SIZE(0..1000))
  MAX-ACCESS read-only
  STATUS current
  DESCRIPTION
    "IPMI unreachable."
  ::= { caEventVariables 37 }

ipmiNetworkConfigFailedEvent OBJECT-TYPE
  SYNTAX OCTET STRING (SIZE(0..1000))
  MAX-ACCESS read-only
  STATUS current
  DESCRIPTION
    "IPMI network configured failed."
  ::= { caEventVariables 38 }

ipmiUserUpdateFailedEvent OBJECT-TYPE
  SYNTAX OCTET STRING (SIZE(0..1000))
  MAX-ACCESS read-only
  STATUS current
  DESCRIPTION
    "IPMI user update failed."
  ::= { caEventVariables 39 }

ipmiConfigAbsentEvent OBJECT-TYPE
  SYNTAX OCTET STRING (SIZE(0..1000))
  MAX-ACCESS read-only
  STATUS current
  DESCRIPTION
    "IPMI config absent in cluster."
  ::= { caEventVariables 40 }

ipmiEventEvent OBJECT-TYPE
  SYNTAX OCTET STRING (SIZE(0..1000))
  MAX-ACCESS read-only
  STATUS current
  DESCRIPTION
    "IPMI enent notification"
  ::= { caEventVariables 41 }

storageDomainQuotaEvent OBJECT-TYPE
  SYNTAX OCTET STRING (SIZE(0..1000))
  MAX-ACCESS read-only
  STATUS current
  DESCRIPTION
    "Storage domain usage exceeded quota alert limit"
  ::= { caEventVariables 42 }

yodaAgentUnhealthyEvent OBJECT-TYPE
  SYNTAX OCTET STRING (SIZE(0..1000))
  MAX-ACCESS read-only
  STATUS current
  DESCRIPTION
    "Yoda agent health check failed."
  ::= { caEventVariables 43 }

searchIndexManualMigrationNeededEvent OBJECT-TYPE
  SYNTAX OCTET STRING (SIZE(0..1000))
  MAX-ACCESS read-only
  STATUS current
  DESCRIPTION
    "Manual Migration to Librarian is required."
  ::= { caEventVariables 44 }

searchIndexMigrationFinishedEvent OBJECT-TYPE
  SYNTAX OCTET STRING (SIZE(0..1000))
  MAX-ACCESS read-only
  STATUS current
  DESCRIPTION
    "Search index migration to Librarian finished."
  ::= { caEventVariables 45 }

searchIndexMigrationTriggeredEvent OBJECT-TYPE
  SYNTAX OCTET STRING (SIZE(0..1000))
  MAX-ACCESS read-only
  STATUS current
  DESCRIPTION
    "Search index migration to Librarian triggered."
  ::= { caEventVariables 46 }

searchIndexMigrationBacklogEvent OBJECT-TYPE
  SYNTAX OCTET STRING (SIZE(0..1000))
  MAX-ACCESS read-only
  STATUS current
  DESCRIPTION
    "Search index migration to Librarian is taking longer than expected."
  ::= { caEventVariables 47 }

vMOptimizedXFSVolumeIndexingSkippedEvent OBJECT-TYPE
  SYNTAX OCTET STRING (SIZE(0..1000))
  MAX-ACCESS read-only
  STATUS current
  DESCRIPTION
    "Optimized XFS indexing path skipped some server volumes."
  ::= { caEventVariables 48 }

vMOptimizedNTFSVolumeIndexingSkippedEvent OBJECT-TYPE
  SYNTAX OCTET STRING (SIZE(0..1000))
  MAX-ACCESS read-only
  STATUS current
  DESCRIPTION
    "Optimized NTFS indexing path skipped some server volumes."
  ::= { caEventVariables 49 }

aVThreatFoundEvent OBJECT-TYPE
  SYNTAX OCTET STRING (SIZE(0..1000))
  MAX-ACCESS read-only
  STATUS current
  DESCRIPTION
    "Virus found by antivirus provider"
  ::= { caEventVariables 50 }

corruptFileSystemNotIndexedEvent OBJECT-TYPE
  SYNTAX OCTET STRING (SIZE(0..1000))
  MAX-ACCESS read-only
  STATUS current
  DESCRIPTION
    "Indexing of object with corrupt filesystem is skipped."
  ::= { caEventVariables 51 }

indexingPausedEvent OBJECT-TYPE
  SYNTAX OCTET STRING (SIZE(0..1000))
  MAX-ACCESS read-only
  STATUS current
  DESCRIPTION
    "Indexing of object contents paused."
  ::= { caEventVariables 52 }

viewQuotaEvent OBJECT-TYPE
  SYNTAX OCTET STRING (SIZE(0..1000))
  MAX-ACCESS read-only
  STATUS current
  DESCRIPTION
    "View usage exceeded quota alert limit"
  ::= { caEventVariables 53 }

usersExceededQuotaEvent OBJECT-TYPE
  SYNTAX OCTET STRING (SIZE(0..1000))
  MAX-ACCESS read-only
  STATUS current
  DESCRIPTION
    "Some users exceeded their logical alert limit"
  ::= { caEventVariables 54 }

notEnoughNodesEvent OBJECT-TYPE
  SYNTAX OCTET STRING (SIZE(0..1000))
  MAX-ACCESS read-only
  STATUS current
  DESCRIPTION
    "More nodes need to be added"
  ::= { caEventVariables 55 }

aVServerLicenseErrorEvent OBJECT-TYPE
  SYNTAX OCTET STRING (SIZE(0..1000))
  MAX-ACCESS read-only
  STATUS current
  DESCRIPTION
    "Antivirus provider license is expired"
  ::= { caEventVariables 56 }

internalSchedulingWarningEvent OBJECT-TYPE
  SYNTAX OCTET STRING (SIZE(0..1000))
  MAX-ACCESS read-only
  STATUS current
  DESCRIPTION
    "Internal scheduling issue"
  ::= { caEventVariables 57 }

cloudTierWarningEvent OBJECT-TYPE
  SYNTAX OCTET STRING (SIZE(0..1000))
  MAX-ACCESS read-only
  STATUS current
  DESCRIPTION
    "Cloud tier warning"
  ::= { caEventVariables 58 }

switchCongestionEvent OBJECT-TYPE
  SYNTAX OCTET STRING (SIZE(0..1000))
  MAX-ACCESS read-only
  STATUS current
  DESCRIPTION
    "Ethernet traffic is experiencing congestion on interface  on node  with ip "
  ::= { caEventVariables 59 }

nodeVirtualizationSupportDisabledEvent OBJECT-TYPE
  SYNTAX OCTET STRING (SIZE(0..1000))
  MAX-ACCESS read-only
  STATUS current
  DESCRIPTION
    "Virtualization support is disabled on node  with ip "
  ::= { caEventVariables 60 }

sshTimeoutChangedEvent OBJECT-TYPE
  SYNTAX OCTET STRING (SIZE(0..1000))
  MAX-ACCESS read-only
  STATUS current
  DESCRIPTION
    "Ssh timeout configuration changed on node  with ip "
  ::= { caEventVariables 61 }

bondUnhealthyEvent OBJECT-TYPE
  SYNTAX OCTET STRING (SIZE(0..1000))
  MAX-ACCESS read-only
  STATUS current
  DESCRIPTION
    "Bond interface is unhealthy on node"
  ::= { caEventVariables 62 }

bondSlavesSpeedInconsistentEvent OBJECT-TYPE
  SYNTAX OCTET STRING (SIZE(0..1000))
  MAX-ACCESS read-only
  STATUS current
  DESCRIPTION
    "Bond slaves' speed are inconsistent on interface  on node  with ip "
  ::= { caEventVariables 63 }

unexpectedInterfaceIpSettingEvent OBJECT-TYPE
  SYNTAX OCTET STRING (SIZE(0..1000))
  MAX-ACCESS read-only
  STATUS current
  DESCRIPTION
    "Static IP on some interfaces is not configured in interface group"
  ::= { caEventVariables 64 }

scriptRunErrorEvent OBJECT-TYPE
  SYNTAX OCTET STRING (SIZE(0..1000))
  MAX-ACCESS read-only
  STATUS current
  DESCRIPTION
    "Health check script  has errors"
  ::= { caEventVariables 65 }

diskIsBadEvent OBJECT-TYPE
  SYNTAX OCTET STRING (SIZE(0..1000))
  MAX-ACCESS read-only
  STATUS current
  DESCRIPTION
    "Disk is bad"
  ::= { caEventVariables 66 }

adDomainControllersNotReachableEvent OBJECT-TYPE
  SYNTAX OCTET STRING (SIZE(0..1000))
  MAX-ACCESS read-only
  STATUS current
  DESCRIPTION
    "Active directory domain controller is not reachable"
  ::= { caEventVariables 67 }

upgradeStuckEvent OBJECT-TYPE
  SYNTAX OCTET STRING (SIZE(0..1000))
  MAX-ACCESS read-only
  STATUS current
  DESCRIPTION
    "Upgrade is taking longer than usual"
  ::= { caEventVariables 68 }

productModelIncompatibleEvent OBJECT-TYPE
  SYNTAX OCTET STRING (SIZE(0..1000))
  MAX-ACCESS read-only
  STATUS current
  DESCRIPTION
    "Product models are not compatible on the node  with ip "
  ::= { caEventVariables 69 }

directoriesExceededQuotaEvent OBJECT-TYPE
  SYNTAX OCTET STRING (SIZE(0..1000))
  MAX-ACCESS read-only
  STATUS current
  DESCRIPTION
    "Some directories exceeded their logical alert limit"
  ::= { caEventVariables 70 }

algorithmBacklogAlertEvent OBJECT-TYPE
  SYNTAX OCTET STRING (SIZE(0..1000))
  MAX-ACCESS read-only
  STATUS current
  DESCRIPTION
    "A background system algorithm is backlogged."
  ::= { caEventVariables 71 }

clearStaleMountPointsTimeoutEvent OBJECT-TYPE
  SYNTAX OCTET STRING (SIZE(0..1000))
  MAX-ACCESS read-only
  STATUS current
  DESCRIPTION
    "Timeout while trying to clear stale mount points."
  ::= { caEventVariables 72 }

addNodeFailedEvent OBJECT-TYPE
  SYNTAX OCTET STRING (SIZE(0..1000))
  MAX-ACCESS read-only
  STATUS current
  DESCRIPTION
    "Node failed to join the cluster"
  ::= { caEventVariables 73 }

directoryExceededQuotaAlertLimitEvent OBJECT-TYPE
  SYNTAX OCTET STRING (SIZE(0..1000))
  MAX-ACCESS read-only
  STATUS current
  DESCRIPTION
    "Directory exceeded the logical alert limit"
  ::= { caEventVariables 74 }

clusterBringupErrorEvent OBJECT-TYPE
  SYNTAX OCTET STRING (SIZE(0..1000))
  MAX-ACCESS read-only
  STATUS current
  DESCRIPTION
    "Error found during cluster bring up on cluster"
  ::= { caEventVariables 75 }

chunkFileBadStateEvent OBJECT-TYPE
  SYNTAX OCTET STRING (SIZE(0..1000))
  MAX-ACCESS read-only
  STATUS current
  DESCRIPTION
    "Chunk file  in Storage domain  is in bad state for long time"
  ::= { caEventVariables 76 }

tablesLargerThanExpectedEvent OBJECT-TYPE
  SYNTAX OCTET STRING (SIZE(0..1000))
  MAX-ACCESS read-only
  STATUS current
  DESCRIPTION
    "Table size, for table is larger than an expected fraction of the disk's metadata capacity"
  ::= { caEventVariables 77 }

keyRotationPolicyChangedEvent OBJECT-TYPE
  SYNTAX OCTET STRING (SIZE(0..1000))
  MAX-ACCESS read-only
  STATUS current
  DESCRIPTION
    "Key rotation policy has been changed."
  ::= { caEventVariables 78 }

potentialClusterErrorEvent OBJECT-TYPE
  SYNTAX OCTET STRING (SIZE(0..1000))
  MAX-ACCESS read-only
  STATUS current
  DESCRIPTION
    "Cluster  might have an internal error that requires action by Cohesity Support"
  ::= { caEventVariables 79 }

clusterGatewayUnReachableEvent OBJECT-TYPE
  SYNTAX OCTET STRING (SIZE(0..1000))
  MAX-ACCESS read-only
  STATUS current
  DESCRIPTION
    "Cluster gateway is not reachable."
  ::= { caEventVariables 80 }

dnsServerUnReachableEvent OBJECT-TYPE
  SYNTAX OCTET STRING (SIZE(0..1000))
  MAX-ACCESS read-only
  STATUS current
  DESCRIPTION
    "DNS server is not reachable."
  ::= { caEventVariables 81 }

verifyVlanHostNameEvent OBJECT-TYPE
  SYNTAX OCTET STRING (SIZE(0..1000))
  MAX-ACCESS read-only
  STATUS current
  DESCRIPTION
    "Error while verifying hostname entry in DNS server for the interface group "
  ::= { caEventVariables 82 }

lowFaultTolerantStorageDomainEvent OBJECT-TYPE
  SYNTAX OCTET STRING (SIZE(0..1000))
  MAX-ACCESS read-only
  STATUS current
  DESCRIPTION
    "Low fault tolerant storage domain found for cluster"
  ::= { caEventVariables 83 }

securityPolicyDenialEvent OBJECT-TYPE
  SYNTAX OCTET STRING (SIZE(0..1000))
  MAX-ACCESS read-only
  STATUS current
  DESCRIPTION
    "Security policy denial found on node  with ip "
  ::= { caEventVariables 84 }

bondModeAutoMigratedEvent OBJECT-TYPE
  SYNTAX OCTET STRING (SIZE(0..1000))
  MAX-ACCESS read-only
  STATUS current
  DESCRIPTION
    "Node  with ip  bond mode has been migrated"
  ::= { caEventVariables 85 }

nisDomainNotReachableEvent OBJECT-TYPE
  SYNTAX OCTET STRING (SIZE(0..1000))
  MAX-ACCESS read-only
  STATUS current
  DESCRIPTION
    "NIS domain  is not reachable."
  ::= { caEventVariables 86 }

nodeRemovedEvent OBJECT-TYPE
  SYNTAX OCTET STRING (SIZE(0..1000))
  MAX-ACCESS read-only
  STATUS current
  DESCRIPTION
    "Node was disconnected or removed"
  ::= { caEventVariables 87 }

nodeInsertedEvent OBJECT-TYPE
  SYNTAX OCTET STRING (SIZE(0..1000))
  MAX-ACCESS read-only
  STATUS current
  DESCRIPTION
    "Node was inserted"
  ::= { caEventVariables 88 }

inconsistentStaticRoutesEvent OBJECT-TYPE
  SYNTAX OCTET STRING (SIZE(0..1000))
  MAX-ACCESS read-only
  STATUS current
  DESCRIPTION
    "One or more inconsistent static routes with cluster config on node  with ip "
  ::= { caEventVariables 89 }

chunkFileInconsistencyEvent OBJECT-TYPE
  SYNTAX OCTET STRING (SIZE(0..1000))
  MAX-ACCESS read-only
  STATUS current
  DESCRIPTION
    "Cluster might have an internal error that requires action by Cohesity Support"
  ::= { caEventVariables 90 }

accessToExternalTargetFailedEvent OBJECT-TYPE
  SYNTAX OCTET STRING (SIZE(0..1000))
  MAX-ACCESS read-only
  STATUS current
  DESCRIPTION
    "Access to external target  failed"
  ::= { caEventVariables 91 }

remoteReplicationBackupUserQuotaSkippedEvent OBJECT-TYPE
  SYNTAX OCTET STRING (SIZE(0..1000))
  MAX-ACCESS read-only
  STATUS current
  DESCRIPTION
    "Replication to remote cluster  for job  skipped user quota data backup"
  ::= { caEventVariables 92 }

remoteReplicationRestoreUserQuotaSkippedEvent OBJECT-TYPE
  SYNTAX OCTET STRING (SIZE(0..1000))
  MAX-ACCESS read-only
  STATUS current
  DESCRIPTION
    "Replication to this cluster skipped user quota data restore"
  ::= { caEventVariables 93 }

remoteReplicationFileSkippedEvent OBJECT-TYPE
  SYNTAX OCTET STRING (SIZE(0..1000))
  MAX-ACCESS read-only
  STATUS current
  DESCRIPTION
    "Replication to remote cluster  for job  skipped unsupported file"
  ::= { caEventVariables 94 }

chunkFileReplicaBadStateEvent OBJECT-TYPE
  SYNTAX OCTET STRING (SIZE(0..1000))
  MAX-ACCESS read-only
  STATUS current
  DESCRIPTION
    "Cluster might have an internal error that requires action by Cohesity Support"
  ::= { caEventVariables 95 }

remoteReplicationSetupIncompatibleEvent OBJECT-TYPE
  SYNTAX OCTET STRING (SIZE(0..1000))
  MAX-ACCESS read-only
  STATUS current
  DESCRIPTION
    "Replication setup is incompatible"
  ::= { caEventVariables 96 }

taskProgressHungEvent OBJECT-TYPE
  SYNTAX OCTET STRING (SIZE(0..1000))
  MAX-ACCESS read-only
  STATUS current
  DESCRIPTION
    "Root task  has some hung sub tasks"
  ::= { caEventVariables 97 }

missingDiskFilesEvent OBJECT-TYPE
  SYNTAX OCTET STRING (SIZE(0..1000))
  MAX-ACCESS read-only
  STATUS current
  DESCRIPTION
    "One or more disk files missing for indexing."
  ::= { caEventVariables 98 }

nodePoweredOffEvent OBJECT-TYPE
  SYNTAX OCTET STRING (SIZE(0..1000))
  MAX-ACCESS read-only
  STATUS current
  DESCRIPTION
    "Node was powered off"
  ::= { caEventVariables 99 }

metadataInconsistencyAlertEvent OBJECT-TYPE
  SYNTAX OCTET STRING (SIZE(0..1000))
  MAX-ACCESS read-only
  STATUS current
  DESCRIPTION
    "Internal error detected for cluster."
  ::= { caEventVariables 100 }

diskMarkedOfflineEvent OBJECT-TYPE
  SYNTAX OCTET STRING (SIZE(0..1000))
  MAX-ACCESS read-only
  STATUS current
  DESCRIPTION
    "Disk is marked offline."
  ::= { caEventVariables 101 }

activeDirectoryNotReachableEvent OBJECT-TYPE
  SYNTAX OCTET STRING (SIZE(0..1000))
  MAX-ACCESS read-only
  STATUS current
  DESCRIPTION
    "Active directory is not reachable."
  ::= { caEventVariables 102 }

kernelPanicEvent OBJECT-TYPE
  SYNTAX OCTET STRING (SIZE(0..1000))
  MAX-ACCESS read-only
  STATUS current
  DESCRIPTION
    "Node crashed from a kernel panic."
  ::= { caEventVariables 103 }

clusterSpaceUsageHighEvent OBJECT-TYPE
  SYNTAX OCTET STRING (SIZE(0..1000))
  MAX-ACCESS read-only
  STATUS current
  DESCRIPTION
    "Cluster space usage is high."
  ::= { caEventVariables 104 }

storageDomainSpaceUsageHighEvent OBJECT-TYPE
  SYNTAX OCTET STRING (SIZE(0..1000))
  MAX-ACCESS read-only
  STATUS current
  DESCRIPTION
    "Storage domain space usage is high."
  ::= { caEventVariables 105 }

nodeFailureIsNotToleratedEvent OBJECT-TYPE
  SYNTAX OCTET STRING (SIZE(0..1000))
  MAX-ACCESS read-only
  STATUS current
  DESCRIPTION
    "Cluster is not able to tolerate node failure."
  ::= { caEventVariables 106 }

searchClusterHealthEvent OBJECT-TYPE
  SYNTAX OCTET STRING (SIZE(0..1000))
  MAX-ACCESS read-only
  STATUS current
  DESCRIPTION
    "Search cluster is not healthy."
  ::= { caEventVariables 107 }

protectionGroupFailedEvent OBJECT-TYPE
  SYNTAX OCTET STRING (SIZE(0..1000))
  MAX-ACCESS read-only
  STATUS current
  DESCRIPTION
    "Backup run of job failed."
  ::= { caEventVariables 108 }

protectedObjectFailedEvent OBJECT-TYPE
  SYNTAX OCTET STRING (SIZE(0..1000))
  MAX-ACCESS read-only
  STATUS current
  DESCRIPTION
    "Backup run of object failed."
  ::= { caEventVariables 109 }

metadataServerUnreachableEvent OBJECT-TYPE
  SYNTAX OCTET STRING (SIZE(0..1000))
  MAX-ACCESS read-only
  STATUS current
  DESCRIPTION
    "Metadata server unreachable for long time."
  ::= { caEventVariables 110 }

metadataUnavailableEvent OBJECT-TYPE
  SYNTAX OCTET STRING (SIZE(0..1000))
  MAX-ACCESS read-only
  STATUS current
  DESCRIPTION
    "Metadata is unavailable due to multiple failures."
  ::= { caEventVariables 111 }

metadataShuffleNotProgressingEvent OBJECT-TYPE
  SYNTAX OCTET STRING (SIZE(0..1000))
  MAX-ACCESS read-only
  STATUS current
  DESCRIPTION
    "Metadata shuffle not progressing due to load constraint."
  ::= { caEventVariables 112 }

searchIndexSizeExceedsThresholdEvent OBJECT-TYPE
  SYNTAX OCTET STRING (SIZE(0..1000))
  MAX-ACCESS read-only
  STATUS current
  DESCRIPTION
    "Search index size is approaching threshold."
  ::= { caEventVariables 113 }

searchIndexShuffleNotProgressingEvent OBJECT-TYPE
  SYNTAX OCTET STRING (SIZE(0..1000))
  MAX-ACCESS read-only
  STATUS current
  DESCRIPTION
    "Data shuffle for search index is not progressing."
  ::= { caEventVariables 114 }

metadataCannotTolerateAnymoreFailuresEvent OBJECT-TYPE
  SYNTAX OCTET STRING (SIZE(0..1000))
  MAX-ACCESS read-only
  STATUS current
  DESCRIPTION
    "Metadata cannot tolerate anymore failures."
  ::= { caEventVariables 115 }

metadataCannotAchieveConfiguredFaultToleranceFactorEvent OBJECT-TYPE
  SYNTAX OCTET STRING (SIZE(0..1000))
  MAX-ACCESS read-only
  STATUS current
  DESCRIPTION
    "Metadata cannot achieve configured fault tolerance factor."
  ::= { caEventVariables 116 }

searchIndexUnavailableEvent OBJECT-TYPE
  SYNTAX OCTET STRING (SIZE(0..1000))
  MAX-ACCESS read-only
  STATUS current
  DESCRIPTION
    "Search index cannot achieve configured fault tolerance factor."
  ::= { caEventVariables 117 }

metadataCanRunOutOfSpaceUponFailureEvent OBJECT-TYPE
  SYNTAX OCTET STRING (SIZE(0..1000))
  MAX-ACCESS read-only
  STATUS current
  DESCRIPTION
    "Metadata can run out of space upon failure."
  ::= { caEventVariables 118 }

diskAddedToBlacklistEvent OBJECT-TYPE
  SYNTAX OCTET STRING (SIZE(0..1000))
  MAX-ACCESS read-only
  STATUS current
  DESCRIPTION
    "Disk is added to blacklist."
  ::= { caEventVariables 119 }

diskSlotAvailableEvent OBJECT-TYPE
  SYNTAX OCTET STRING (SIZE(0..1000))
  MAX-ACCESS read-only
  STATUS current
  DESCRIPTION
    "One or more unused disk slots are available."
  ::= { caEventVariables 120 }

protectionGroupSlaViolatedEvent OBJECT-TYPE
  SYNTAX OCTET STRING (SIZE(0..1000))
  MAX-ACCESS read-only
  STATUS current
  DESCRIPTION
    "SLA of backup run of job violated."
  ::= { caEventVariables 121 }

protectionGroupcanceledBlackoutWindowEvent OBJECT-TYPE
  SYNTAX OCTET STRING (SIZE(0..1000))
  MAX-ACCESS read-only
  STATUS current
  DESCRIPTION
    "Backup run of job was cancelled due to hitting blackout window."
  ::= { caEventVariables 122 }

policyFieldsDeprecatedEvent OBJECT-TYPE
  SYNTAX OCTET STRING (SIZE(0..1000))
  MAX-ACCESS read-only
  STATUS current
  DESCRIPTION
    "Policy settings of a policy have been deprecated."
  ::= { caEventVariables 123 }

protectedObjectCancelledBlackoutWindowEvent OBJECT-TYPE
  SYNTAX OCTET STRING (SIZE(0..1000))
  MAX-ACCESS read-only
  STATUS current
  DESCRIPTION
    "Backup of object that is part of job run was cancelled due to blackout window."
  ::= { caEventVariables 124 }

protectionGroupArchivalBacklogEvent OBJECT-TYPE
  SYNTAX OCTET STRING (SIZE(0..1000))
  MAX-ACCESS read-only
  STATUS current
  DESCRIPTION
    "Backup job has archival tasks with high queue wait times."
  ::= { caEventVariables 125 }

archiveJobFailedEvent OBJECT-TYPE
  SYNTAX OCTET STRING (SIZE(0..1000))
  MAX-ACCESS read-only
  STATUS current
  DESCRIPTION
    "Archive task has failed."
  ::= { caEventVariables 126 }

archiveJobStuckEvent OBJECT-TYPE
  SYNTAX OCTET STRING (SIZE(0..1000))
  MAX-ACCESS read-only
  STATUS current
  DESCRIPTION
    "Archive task is not making progress."
  ::= { caEventVariables 127 }

restoreJobFailedEvent OBJECT-TYPE
  SYNTAX OCTET STRING (SIZE(0..1000))
  MAX-ACCESS read-only
  STATUS current
  DESCRIPTION
    "Restore task has progress."
  ::= { caEventVariables 128 }

restoreJobStuckEvent OBJECT-TYPE
  SYNTAX OCTET STRING (SIZE(0..1000))
  MAX-ACCESS read-only
  STATUS current
  DESCRIPTION
    "Restore task is not making progress."
  ::= { caEventVariables 129 }

protectedObjectSlaViolatedEvent OBJECT-TYPE
  SYNTAX OCTET STRING (SIZE(0..1000))
  MAX-ACCESS read-only
  STATUS current
  DESCRIPTION
    "Backup of object violated SLA in a backup run."
  ::= { caEventVariables 130 }

protectionGroupReplicationBacklogEvent OBJECT-TYPE
  SYNTAX OCTET STRING (SIZE(0..1000))
  MAX-ACCESS read-only
  STATUS current
  DESCRIPTION
    "Backup job has replication tasks with high queue wait times."
  ::= { caEventVariables 131 }

missingVMBackupEvent OBJECT-TYPE
  SYNTAX OCTET STRING (SIZE(0..1000))
  MAX-ACCESS read-only
  STATUS current
  DESCRIPTION
    "Missing VM Backup."
  ::= { caEventVariables 132 }

vMCrackingSkippedEvent OBJECT-TYPE
  SYNTAX OCTET STRING (SIZE(0..1000))
  MAX-ACCESS read-only
  STATUS current
  DESCRIPTION
    "VM contents not indexed."
  ::= { caEventVariables 133 }

vMWareMountFailureEvent OBJECT-TYPE
  SYNTAX OCTET STRING (SIZE(0..1000))
  MAX-ACCESS read-only
  STATUS current
  DESCRIPTION
    "Too many VMWare mount failures."
  ::= { caEventVariables 134 }

vMVolumeIndexingSkippedEvent OBJECT-TYPE
  SYNTAX OCTET STRING (SIZE(0..1000))
  MAX-ACCESS read-only
  STATUS current
  DESCRIPTION
    "VM one or more volume indexing skipped."
  ::= { caEventVariables 135 }

remoteReplicationTaskStuckEvent OBJECT-TYPE
  SYNTAX OCTET STRING (SIZE(0..1000))
  MAX-ACCESS read-only
  STATUS current
  DESCRIPTION
    "Replication to remote cluster is stuck for a job."
  ::= { caEventVariables 136 }

remoteReplicationTaskFailedEvent OBJECT-TYPE
  SYNTAX OCTET STRING (SIZE(0..1000))
  MAX-ACCESS read-only
  STATUS current
  DESCRIPTION
    "Replication to remote cluster has failed for a job."
  ::= { caEventVariables 137 }

frequentProcessRestartsEvent OBJECT-TYPE
  SYNTAX OCTET STRING (SIZE(0..1000))
  MAX-ACCESS read-only
  STATUS current
  DESCRIPTION
    "Process is being restarted frequently."
  ::= { caEventVariables 138 }

protectionGroupProgressingSlowlyEvent OBJECT-TYPE
  SYNTAX OCTET STRING (SIZE(0..1000))
  MAX-ACCESS read-only
  STATUS current
  DESCRIPTION
    "Protection group is progressing slowly."
  ::= { caEventVariables 139 }

mtuUnexpectedEvent OBJECT-TYPE
  SYNTAX OCTET STRING (SIZE(0..1000))
  MAX-ACCESS read-only
  STATUS current
  DESCRIPTION
    "MTU does not match expected configuration on the node  with ip "
  ::= { caEventVariables 140 }

gatewayUnexpectedEvent OBJECT-TYPE
  SYNTAX OCTET STRING (SIZE(0..1000))
  MAX-ACCESS read-only
  STATUS current
  DESCRIPTION
    "Gateway does not match expected configuration on the node  with ip "
  ::= { caEventVariables 141 }

linkStatsIsNotNormalEvent OBJECT-TYPE
  SYNTAX OCTET STRING (SIZE(0..1000))
  MAX-ACCESS read-only
  STATUS current
  DESCRIPTION
    "Errors detected in the network Physical layer"
  ::= { caEventVariables 142 }

upgradeSucceededEvent OBJECT-TYPE
  SYNTAX OCTET STRING (SIZE(0..1000))
  MAX-ACCESS read-only
  STATUS current
  DESCRIPTION
    "Upgrade succeeded on the node to "
  ::= { caEventVariables 143 }

upgradeStartedEvent OBJECT-TYPE
  SYNTAX OCTET STRING (SIZE(0..1000))
  MAX-ACCESS read-only
  STATUS current
  DESCRIPTION
    "Upgrade started on the node"
  ::= { caEventVariables 144 }

bondingModeUnexpectedEvent OBJECT-TYPE
  SYNTAX OCTET STRING (SIZE(0..1000))
  MAX-ACCESS read-only
  STATUS current
  DESCRIPTION
    "Bonding mode does not match expected configuration on the node"
  ::= { caEventVariables 145 }

vLANUnexpectedEvent OBJECT-TYPE
  SYNTAX OCTET STRING (SIZE(0..1000))
  MAX-ACCESS read-only
  STATUS current
  DESCRIPTION
    "Unexpected VLAN found on node  with ip ."
  ::= { caEventVariables 146 }

kIntegralVolumeReachingMaxCapacityEvent OBJECT-TYPE
  SYNTAX OCTET STRING (SIZE(0..1000))
  MAX-ACCESS read-only
  STATUS current
  DESCRIPTION
    "Current integral volume on QStar host reaching its max capacity limit."
  ::= { caEventVariables 147 }

mediaErrorDuringRestoreEvent OBJECT-TYPE
  SYNTAX OCTET STRING (SIZE(0..1000))
  MAX-ACCESS read-only
  STATUS current
  DESCRIPTION
    "Restore task is waiting to correct the error"
  ::= { caEventVariables 148 }

mediaErrorDuringArchivalEvent OBJECT-TYPE
  SYNTAX OCTET STRING (SIZE(0..1000))
  MAX-ACCESS read-only
  STATUS current
  DESCRIPTION
    "Archival job is waiting to correct the error"
  ::= { caEventVariables 149 }

diskWithTooManyDeltaRecordsEvent OBJECT-TYPE
  SYNTAX OCTET STRING (SIZE(0..1000))
  MAX-ACCESS read-only
  STATUS current
  DESCRIPTION
    "Disk  has too many internal metadata records"
  ::= { caEventVariables 150 }

unresponsiveChildDeathEvent OBJECT-TYPE
  SYNTAX OCTET STRING (SIZE(0..1000))
  MAX-ACCESS read-only
  STATUS current
  DESCRIPTION
    "Process  is unresponsive"
  ::= { caEventVariables 151 }

encryptionKeyRotatedEvent OBJECT-TYPE
  SYNTAX OCTET STRING (SIZE(0..1000))
  MAX-ACCESS read-only
  STATUS current
  DESCRIPTION
    "Encryption key has been rotated."
  ::= { caEventVariables 152 }

encryptionKeyCreatedEvent OBJECT-TYPE
  SYNTAX OCTET STRING (SIZE(0..1000))
  MAX-ACCESS read-only
  STATUS current
  DESCRIPTION
    "A new encryption key has been created."
  ::= { caEventVariables 153 }

newUpgradePackagesAvailableEvent OBJECT-TYPE
  SYNTAX OCTET STRING (SIZE(0..1000))
  MAX-ACCESS read-only
  STATUS current
  DESCRIPTION
    "New upgrade packages available on the node  with IP  to "
  ::= { caEventVariables 154 }

invalidStateEvent OBJECT-TYPE
  SYNTAX OCTET STRING (SIZE(0..1000))
  MAX-ACCESS read-only
  STATUS current
  DESCRIPTION
    "Node  with ip  entered an invalid state"
  ::= { caEventVariables 155 }

metadataSizeExceedsThresholdEvent OBJECT-TYPE
  SYNTAX OCTET STRING (SIZE(0..1000))
  MAX-ACCESS read-only
  STATUS current
  DESCRIPTION
    "Metadata size on disk exceeding threshold"
  ::= { caEventVariables 156 }

keystoneNotReachableEvent OBJECT-TYPE
  SYNTAX OCTET STRING (SIZE(0..1000))
  MAX-ACCESS read-only
  STATUS current
  DESCRIPTION
    "Keystone  is not reachable."
  ::= { caEventVariables 157 }

dataResilienceAtRiskEvent OBJECT-TYPE
  SYNTAX OCTET STRING (SIZE(0..1000))
  MAX-ACCESS read-only
  STATUS current
  DESCRIPTION
    "Data resilience at risk"
  ::= { caEventVariables 158 }

diskAwaitHighEvent OBJECT-TYPE
  SYNTAX OCTET STRING (SIZE(0..1000))
  MAX-ACCESS read-only
  STATUS current
  DESCRIPTION
    "Await time for disk ID is too high"
  ::= { caEventVariables 159 }

raidInactiveEvent OBJECT-TYPE
  SYNTAX OCTET STRING (SIZE(0..1000))
  MAX-ACCESS read-only
  STATUS current
  DESCRIPTION
    "Node  with ip  has inactive RAID disks "
  ::= { caEventVariables 160 }

removeNodeSuccessEvent OBJECT-TYPE
  SYNTAX OCTET STRING (SIZE(0..1000))
  MAX-ACCESS read-only
  STATUS current
  DESCRIPTION
    "Removal of node is successful"
  ::= { caEventVariables 161 }

routesMigrationOnBondFailedEvent OBJECT-TYPE
  SYNTAX OCTET STRING (SIZE(0..1000))
  MAX-ACCESS read-only
  STATUS current
  DESCRIPTION
    "Node  with ip  routes migration to bond failed"
  ::= { caEventVariables 162 }

serviceDownEvent OBJECT-TYPE
  SYNTAX OCTET STRING (SIZE(0..1000))
  MAX-ACCESS read-only
  STATUS current
  DESCRIPTION
    " service on the node  with ip  is down"
  ::= { caEventVariables 163 }

configureVipFailedEvent OBJECT-TYPE
  SYNTAX OCTET STRING (SIZE(0..1000))
  MAX-ACCESS read-only
  STATUS current
  DESCRIPTION
    "Failed to configure VIP"
  ::= { caEventVariables 164 }

ipMigrationOnBondFailedEvent OBJECT-TYPE
  SYNTAX OCTET STRING (SIZE(0..1000))
  MAX-ACCESS read-only
  STATUS current
  DESCRIPTION
    "Node  with ip  IP migration to bond failed"
  ::= { caEventVariables 165 }

firewallErrorEvent OBJECT-TYPE
  SYNTAX OCTET STRING (SIZE(0..1000))
  MAX-ACCESS read-only
  STATUS current
  DESCRIPTION
    "Cluster firewall on node has errors"
  ::= { caEventVariables 166 }

usbDiskFoundEvent OBJECT-TYPE
  SYNTAX OCTET STRING (SIZE(0..1000))
  MAX-ACCESS read-only
  STATUS current
  DESCRIPTION
    "Usb disk  detected on the node  with ip "
  ::= { caEventVariables 167 }

bootDiskHealthEvent OBJECT-TYPE
  SYNTAX OCTET STRING (SIZE(0..1000))
  MAX-ACCESS read-only
  STATUS current
  DESCRIPTION
    "Boot disk maybe unhealthy on the node  with ip "
  ::= { caEventVariables 168 }

etcHostsFileErrorEvent OBJECT-TYPE
  SYNTAX OCTET STRING (SIZE(0..1000))
  MAX-ACCESS read-only
  STATUS current
  DESCRIPTION
    "Etc hosts file on node  with ip  has errors"
  ::= { caEventVariables 169 }

smallMemorySizeEvent OBJECT-TYPE
  SYNTAX OCTET STRING (SIZE(0..1000))
  MAX-ACCESS read-only
  STATUS current
  DESCRIPTION
    "Node  with ip  does not meet minimum memory size requirements"
  ::= { caEventVariables 170 }

userExceededQuotaAlertLimitEvent OBJECT-TYPE
  SYNTAX OCTET STRING (SIZE(0..1000))
  MAX-ACCESS read-only
  STATUS current
  DESCRIPTION
    "User exceeded the logical alert limit"
  ::= { caEventVariables 171 }

addNodeSuccessEvent OBJECT-TYPE
  SYNTAX OCTET STRING (SIZE(0..1000))
  MAX-ACCESS read-only
  STATUS current
  DESCRIPTION
    "Node has joined the cluster"
  ::= { caEventVariables 172 }

forcefulRemoveNodeWarningEvent OBJECT-TYPE
  SYNTAX OCTET STRING (SIZE(0..1000))
  MAX-ACCESS read-only
  STATUS current
  DESCRIPTION
    "Node is being removed from the cluster forcefully"
  ::= { caEventVariables 173 }

aVServerConnectionFailedEvent OBJECT-TYPE
  SYNTAX OCTET STRING (SIZE(0..1000))
  MAX-ACCESS read-only
  STATUS current
  DESCRIPTION
    "Antivirus provider is not reachable"
  ::= { caEventVariables 174 }

adPreferredDomainControllerNotReachableEvent OBJECT-TYPE
  SYNTAX OCTET STRING (SIZE(0..1000))
  MAX-ACCESS read-only
  STATUS current
  DESCRIPTION
    "Preferred domain controller is not reachable"
  ::= { caEventVariables 175 }

blobJournalInconsistencyEvent OBJECT-TYPE
  SYNTAX OCTET STRING (SIZE(0..1000))
  MAX-ACCESS read-only
  STATUS current
  DESCRIPTION
    "Cluster might have an internal error that requires action by Cohesity Support"
  ::= { caEventVariables 176 }

viewLatencyHighEvent OBJECT-TYPE
  SYNTAX OCTET STRING (SIZE(0..1000))
  MAX-ACCESS read-only
  STATUS current
  DESCRIPTION
    "View latency exceeds threshold"
  ::= { caEventVariables 177 }

potentialMinorClusterErrorEvent OBJECT-TYPE
  SYNTAX OCTET STRING (SIZE(0..1000))
  MAX-ACCESS read-only
  STATUS current
  DESCRIPTION
    "Cluster  might have an internal error that requires action by Cohesity Support"
  ::= { caEventVariables 178 }

iceboxDedupCacheFullEvent OBJECT-TYPE
  SYNTAX OCTET STRING (SIZE(0..1000))
  MAX-ACCESS read-only
  STATUS current
  DESCRIPTION
    "Icebox dedup cache is full"
  ::= { caEventVariables 179 }

clusterServiceGflagsFoundEvent OBJECT-TYPE
  SYNTAX OCTET STRING (SIZE(0..1000))
  MAX-ACCESS read-only
  STATUS current
  DESCRIPTION
    "Found cluster service gflags."
  ::= { caEventVariables 180 }

virtualApplianceResourcesUnexpectedEvent OBJECT-TYPE
  SYNTAX OCTET STRING (SIZE(0..1000))
  MAX-ACCESS read-only
  STATUS current
  DESCRIPTION
    "The resources for the virtual appliance on node is not matching Cohesity recommendations"
  ::= { caEventVariables 181 }

clusterPartitionCreateFailedEvent OBJECT-TYPE
  SYNTAX OCTET STRING (SIZE(0..1000))
  MAX-ACCESS read-only
  STATUS current
  DESCRIPTION
    "Could not create cluster partition."
  ::= { caEventVariables 182 }

proxyServerUnreachableEvent OBJECT-TYPE
  SYNTAX OCTET STRING (SIZE(0..1000))
  MAX-ACCESS read-only
  STATUS current
  DESCRIPTION
    "Proxy server is unreachable on the node  with ip "
  ::= { caEventVariables 183 }

serviceVersionsMismatchedEvent OBJECT-TYPE
  SYNTAX OCTET STRING (SIZE(0..1000))
  MAX-ACCESS read-only
  STATUS current
  DESCRIPTION
    "Cohesity nodes are running different versions of software in the same cluster"
  ::= { caEventVariables 184 }

firmwareIncompatibleEvent OBJECT-TYPE
  SYNTAX OCTET STRING (SIZE(0..1000))
  MAX-ACCESS read-only
  STATUS current
  DESCRIPTION
    "Node  with ip  firmware is incompatible"
  ::= { caEventVariables 185 }

nodeRebootedForYodaStuckEvent OBJECT-TYPE
  SYNTAX OCTET STRING (SIZE(0..1000))
  MAX-ACCESS read-only
  STATUS current
  DESCRIPTION
    "Node  with ip  is being rebooted as yoda is stuck"
  ::= { caEventVariables 186 }

protectionGroupSucceededEvent OBJECT-TYPE
  SYNTAX OCTET STRING (SIZE(0..1000))
  MAX-ACCESS read-only
  STATUS current
  DESCRIPTION
    "Backup run of protection group  of type  completed successfully"
  ::= { caEventVariables 187 }

unregisterExternalTargetFailedEvent OBJECT-TYPE
  SYNTAX OCTET STRING (SIZE(0..1000))
  MAX-ACCESS read-only
  STATUS current
  DESCRIPTION
    "Unregistration for external target  failed."
  ::= { caEventVariables 188 }

licenseServerUnreachableEvent OBJECT-TYPE
  SYNTAX OCTET STRING (SIZE(0..1000))
  MAX-ACCESS read-only
  STATUS current
  DESCRIPTION
    "License server is unreachable."
  ::= { caEventVariables 189 }

invalidLicenseEvent OBJECT-TYPE
  SYNTAX OCTET STRING (SIZE(0..1000))
  MAX-ACCESS read-only
  STATUS current
  DESCRIPTION
    "License is invalid."
  ::= { caEventVariables 190 }

unlicensedClusterEvent OBJECT-TYPE
  SYNTAX OCTET STRING (SIZE(0..1000))
  MAX-ACCESS read-only
  STATUS current
  DESCRIPTION
    "Cluster is unlicensed."
  ::= { caEventVariables 191 }

verifyRemoteClusterConnectionEvent OBJECT-TYPE
  SYNTAX OCTET STRING (SIZE(0..1000))
  MAX-ACCESS read-only
  STATUS current
  DESCRIPTION
    "Verify remote cluster connection and associated static route."
  ::= { caEventVariables 192 }

sysSrvcErrorsEvent OBJECT-TYPE
  SYNTAX OCTET STRING (SIZE(0..1000))
  MAX-ACCESS read-only
  STATUS current
  DESCRIPTION
    "Node  with ip  have errors in system service logs"
  ::= { caEventVariables 193 }

bridgeMigrationFailedEvent OBJECT-TYPE
  SYNTAX OCTET STRING (SIZE(0..1000))
  MAX-ACCESS read-only
  STATUS current
  DESCRIPTION
    "Bridge Migrate failed on node  with ip "
  ::= { caEventVariables 194 }

bridgeMigrationRevertFailedEvent OBJECT-TYPE
  SYNTAX OCTET STRING (SIZE(0..1000))
  MAX-ACCESS read-only
  STATUS current
  DESCRIPTION
    "Bridge migration revert failed on node  with ip "
  ::= { caEventVariables 195 }

productModelInterfacesInconsistencyEvent OBJECT-TYPE
  SYNTAX OCTET STRING (SIZE(0..1000))
  MAX-ACCESS read-only
  STATUS current
  DESCRIPTION
    "Network interfaces inconsistency exists on cluster nodes. Network interfaces need to be consistent across nodes on same product model."
  ::= { caEventVariables 196 }

clusterInterfacesInconsistencyEvent OBJECT-TYPE
  SYNTAX OCTET STRING (SIZE(0..1000))
  MAX-ACCESS read-only
  STATUS current
  DESCRIPTION
    "Network interfaces inconsistency exists on different product models in heterogeneous cluster."
  ::= { caEventVariables 197 }

ntpServerUnReachableEvent OBJECT-TYPE
  SYNTAX OCTET STRING (SIZE(0..1000))
  MAX-ACCESS read-only
  STATUS current
  DESCRIPTION
    "NTP server is not reachable."
  ::= { caEventVariables 198 }

externalTargetNotReachableEvent OBJECT-TYPE
  SYNTAX OCTET STRING (SIZE(0..1000))
  MAX-ACCESS read-only
  STATUS current
  DESCRIPTION
    "External target  not reachable from node."
  ::= { caEventVariables 199 }

appInstanceUnhealthyEvent OBJECT-TYPE
  SYNTAX OCTET STRING (SIZE(0..1000))
  MAX-ACCESS read-only
  STATUS current
  DESCRIPTION
    "Detected unhealthy instance  at "
  ::= { caEventVariables 200 }

indexingBacklogEvent OBJECT-TYPE
  SYNTAX OCTET STRING (SIZE(0..1000))
  MAX-ACCESS read-only
  STATUS current
  DESCRIPTION
    "Backlog in indexing of VM contents."
  ::= { caEventVariables 201 }

searchNodeBusyEvent OBJECT-TYPE
  SYNTAX OCTET STRING (SIZE(0..1000))
  MAX-ACCESS read-only
  STATUS current
  DESCRIPTION
    "Search node is using more than 80% of cpu on machine."
  ::= { caEventVariables 202 }

nonEmptyUnmountedDirectoryEvent OBJECT-TYPE
  SYNTAX OCTET STRING (SIZE(0..1000))
  MAX-ACCESS read-only
  STATUS current
  DESCRIPTION
    "Unmounted directory is not empty, it has some entries."
  ::= { caEventVariables 203 }

rhinoUnhealthyEvent OBJECT-TYPE
  SYNTAX OCTET STRING (SIZE(0..1000))
  MAX-ACCESS read-only
  STATUS current
  DESCRIPTION
    "Too many Rhino healthchecks failed."
  ::= { caEventVariables 204 }

lessCPUCoreEvent OBJECT-TYPE
  SYNTAX OCTET STRING (SIZE(0..1000))
  MAX-ACCESS read-only
  STATUS current
  DESCRIPTION
    "Node  with ip  does not meet minimum CPU core count requirements"
  ::= { caEventVariables 205 }

licenseExpiredEvent OBJECT-TYPE
  SYNTAX OCTET STRING (SIZE(0..1000))
  MAX-ACCESS read-only
  STATUS current
  DESCRIPTION
    "License has expired."
  ::= { caEventVariables 206 }

licenseAboutToExpireEvent OBJECT-TYPE
  SYNTAX OCTET STRING (SIZE(0..1000))
  MAX-ACCESS read-only
  STATUS current
  DESCRIPTION
    "License is about to expire."
  ::= { caEventVariables 207 }

biosAndBmcVersionMismatchEvent OBJECT-TYPE
  SYNTAX OCTET STRING (SIZE(0..1000))
  MAX-ACCESS read-only
  STATUS current
  DESCRIPTION
    "Node on the cluster has incompatible BIOS/BMC version"
  ::= { caEventVariables 208 }

unusedGflagsEvent OBJECT-TYPE
  SYNTAX OCTET STRING (SIZE(0..1000))
  MAX-ACCESS read-only
  STATUS current
  DESCRIPTION
    "Node  with ip  has gflags that are no longer in use"
  ::= { caEventVariables 209 }

supportChannelAboutToCloseEvent OBJECT-TYPE
  SYNTAX OCTET STRING (SIZE(0..1000))
  MAX-ACCESS read-only
  STATUS current
  DESCRIPTION
    "Cohesity support channel about to close on cluster with ID "
  ::= { caEventVariables 210 }

licenseAccountOverUseEvent OBJECT-TYPE
  SYNTAX OCTET STRING (SIZE(0..1000))
  MAX-ACCESS read-only
  STATUS current
  DESCRIPTION
    "Licensed account is overused."
  ::= { caEventVariables 211 }

licenseIdentityInvalidEvent OBJECT-TYPE
  SYNTAX OCTET STRING (SIZE(0..1000))
  MAX-ACCESS read-only
  STATUS current
  DESCRIPTION
    "License identity is invalid."
  ::= { caEventVariables 212 }

kMSCertificateWillExpireEvent OBJECT-TYPE
  SYNTAX OCTET STRING (SIZE(0..1000))
  MAX-ACCESS read-only
  STATUS current
  DESCRIPTION
    "A KMS server certificate will expire soon."
  ::= { caEventVariables 213 }

kMSCertificateExpirationEvent OBJECT-TYPE
  SYNTAX OCTET STRING (SIZE(0..1000))
  MAX-ACCESS read-only
  STATUS current
  DESCRIPTION
    "A KMS server certificate has expired."
  ::= { caEventVariables 214 }

kMSErrorEvent OBJECT-TYPE
  SYNTAX OCTET STRING (SIZE(0..1000))
  MAX-ACCESS read-only
  STATUS current
  DESCRIPTION
    "An error was received while communicating with the key management server."
  ::= { caEventVariables 215 }

keyObjectCreatedEvent OBJECT-TYPE
  SYNTAX OCTET STRING (SIZE(0..1000))
  MAX-ACCESS read-only
  STATUS current
  DESCRIPTION
    "A key object has been created."
  ::= { caEventVariables 216 }

keyObjectDestroyedEvent OBJECT-TYPE
  SYNTAX OCTET STRING (SIZE(0..1000))
  MAX-ACCESS read-only
  STATUS current
  DESCRIPTION
    "A key object has been destroyed."
  ::= { caEventVariables 217 }

kMSUnreachableEvent OBJECT-TYPE
  SYNTAX OCTET STRING (SIZE(0..1000))
  MAX-ACCESS read-only
  STATUS current
  DESCRIPTION
    "A KMS server is unreachable."
  ::= { caEventVariables 218 }

diskMarkedForRemovalEvent OBJECT-TYPE
  SYNTAX OCTET STRING (SIZE(0..1000))
  MAX-ACCESS read-only
  STATUS current
  DESCRIPTION
    "Disk  marked for removal"
  ::= { caEventVariables 219 }

nodeMarkedForRemovalEvent OBJECT-TYPE
  SYNTAX OCTET STRING (SIZE(0..1000))
  MAX-ACCESS read-only
  STATUS current
  DESCRIPTION
    "Node is marked for removal from cluster"
  ::= { caEventVariables 220 }

addNodesStartedEvent OBJECT-TYPE
  SYNTAX OCTET STRING (SIZE(0..1000))
  MAX-ACCESS read-only
  STATUS current
  DESCRIPTION
    "Node is joining the cluster"
  ::= { caEventVariables 221 }

diskRemovedEvent OBJECT-TYPE
  SYNTAX OCTET STRING (SIZE(0..1000))
  MAX-ACCESS read-only
  STATUS current
  DESCRIPTION
    "Disk  with serial  in slot  is removed from node  with ip "
  ::= { caEventVariables 222 }

sshKeyMismatchEvent OBJECT-TYPE
  SYNTAX OCTET STRING (SIZE(0..1000))
  MAX-ACCESS read-only
  STATUS current
  DESCRIPTION
    "Check Failed : All nodes in the cluster must have same ssh keys!"
  ::= { caEventVariables 223 }

bMCModuleNotAvailableEvent OBJECT-TYPE
  SYNTAX OCTET STRING (SIZE(0..1000))
  MAX-ACCESS read-only
  STATUS current
  DESCRIPTION
    "BMC module is not available on node  with ip "
  ::= { caEventVariables 224 }

outOfMemoryRestartEvent OBJECT-TYPE
  SYNTAX OCTET STRING (SIZE(0..1000))
  MAX-ACCESS read-only
  STATUS current
  DESCRIPTION
    "Process  restarted due to out of memory"
  ::= { caEventVariables 225 }

metadataInstanceHasUnrecoverableErrorEvent OBJECT-TYPE
  SYNTAX OCTET STRING (SIZE(0..1000))
  MAX-ACCESS read-only
  STATUS current
  DESCRIPTION
    "A corruption has been detected on disk "
  ::= { caEventVariables 226 }

metadataDiskRanOutOfSpaceEvent OBJECT-TYPE
  SYNTAX OCTET STRING (SIZE(0..1000))
  MAX-ACCESS read-only
  STATUS current
  DESCRIPTION
    "Scribe reservation increased failed"
  ::= { caEventVariables 227 }

licenseStatsHistoryCollectionEvent OBJECT-TYPE
  SYNTAX OCTET STRING (SIZE(0..1000))
  MAX-ACCESS read-only
  STATUS current
  DESCRIPTION
    "License stats history collection"
  ::= { caEventVariables 228 }

dnsServerConnectionFailedEvent OBJECT-TYPE
  SYNTAX OCTET STRING (SIZE(0..1000))
  MAX-ACCESS read-only
  STATUS current
  DESCRIPTION
    "DNS server is not reachable"
  ::= { caEventVariables 229 }

nASVaultIsFullEvent OBJECT-TYPE
  SYNTAX OCTET STRING (SIZE(0..1000))
  MAX-ACCESS read-only
  STATUS current
  DESCRIPTION
    "NAS External target is full"
  ::= { caEventVariables 230 }

protectionGroupReplicationFailedEvent OBJECT-TYPE
  SYNTAX OCTET STRING (SIZE(0..1000))
  MAX-ACCESS read-only
  STATUS current
  DESCRIPTION
    "Replication to remote cluster failed"
  ::= { caEventVariables 231 }

diskIdMismatchEvent OBJECT-TYPE
  SYNTAX OCTET STRING (SIZE(0..1000))
  MAX-ACCESS read-only
  STATUS current
  DESCRIPTION
    "Metadata Disk re-addition error due to improper disk removal, expected disk ID is different from saved disk ID"
  ::= { caEventVariables 232 }

continuousDataProtectionDisabledEvent OBJECT-TYPE
  SYNTAX OCTET STRING (SIZE(0..1000))
  MAX-ACCESS read-only
  STATUS current
  DESCRIPTION
    "CDP is disabled for VM, Protection Group ID"
  ::= { caEventVariables 233 }

protectionPolicyDeletedEvent OBJECT-TYPE
  SYNTAX OCTET STRING (SIZE(0..1000))
  MAX-ACCESS read-only
  STATUS current
  DESCRIPTION
    "Protection Policy was deleted"
  ::= { caEventVariables 234 }

objectBackupSlaViolatedEvent OBJECT-TYPE
  SYNTAX OCTET STRING (SIZE(0..1000))
  MAX-ACCESS read-only
  STATUS current
  DESCRIPTION
    "SLA for backup of object  is violated"
  ::= { caEventVariables 235 }

objectBackupFailedEvent OBJECT-TYPE
  SYNTAX OCTET STRING (SIZE(0..1000))
  MAX-ACCESS read-only
  STATUS current
  DESCRIPTION
    "Backup of  of type  failed with error "
  ::= { caEventVariables 236 }

auditLogFailureEvent OBJECT-TYPE
  SYNTAX OCTET STRING (SIZE(0..1000))
  MAX-ACCESS read-only
  STATUS current
  DESCRIPTION
    "Cluster  is at risk of failing to process audit logs as required"
  ::= { caEventVariables 237 }

silicomNicFoundEvent OBJECT-TYPE
  SYNTAX OCTET STRING (SIZE(0..1000))
  MAX-ACCESS read-only
  STATUS current
  DESCRIPTION
    "Found Silicom NIC in node  wit ip "
  ::= { caEventVariables 238 }

diskRemovalCancelledEvent OBJECT-TYPE
  SYNTAX OCTET STRING (SIZE(0..1000))
  MAX-ACCESS read-only
  STATUS current
  DESCRIPTION
    "Disk removal is cancelled."
  ::= { caEventVariables 239 }

metadataMigrationsNotProgressingEvent OBJECT-TYPE
  SYNTAX OCTET STRING (SIZE(0..1000))
  MAX-ACCESS read-only
  STATUS current
  DESCRIPTION
    "Metadata migrations not progressing."
  ::= { caEventVariables 240 }

manualBackgroundSystemThrottlingAppliedEvent OBJECT-TYPE
  SYNTAX OCTET STRING (SIZE(0..1000))
  MAX-ACCESS read-only
  STATUS current
  DESCRIPTION
    "Manual throttling of background system algorithms applied."
  ::= { caEventVariables 241 }

remoteStorageUsageHighEvent OBJECT-TYPE
  SYNTAX OCTET STRING (SIZE(0..1000))
  MAX-ACCESS read-only
  STATUS current
  DESCRIPTION
    "Remote storage usage is high."
  ::= { caEventVariables 242 }

remoteStorageCapacityChangedEvent OBJECT-TYPE
  SYNTAX OCTET STRING (SIZE(0..1000))
  MAX-ACCESS read-only
  STATUS current
  DESCRIPTION
    "Remote storage capacity has changed."
  ::= { caEventVariables 243 }

routingDaemonDownEvent OBJECT-TYPE
  SYNTAX OCTET STRING (SIZE(0..1000))
  MAX-ACCESS read-only
  STATUS current
  DESCRIPTION
    "Routing daemon is down."
  ::= { caEventVariables 244 }

remoteStorageManagementIpUnreachableEvent OBJECT-TYPE
  SYNTAX OCTET STRING (SIZE(0..1000))
  MAX-ACCESS read-only
  STATUS current
  DESCRIPTION
    "Remote storage Management IP is unreachable."
  ::= { caEventVariables 245 }

remoteStorageFileSystemMountFailedEvent OBJECT-TYPE
  SYNTAX OCTET STRING (SIZE(0..1000))
  MAX-ACCESS read-only
  STATUS current
  DESCRIPTION
    "Failed to mount NFS file system  from Pure Flash Array "
  ::= { caEventVariables 246 }

remoteStorageFileSystemDeletedEvent OBJECT-TYPE
  SYNTAX OCTET STRING (SIZE(0..1000))
  MAX-ACCESS read-only
  STATUS current
  DESCRIPTION
    "File system  on Pure Flash Array  is deleted"
  ::= { caEventVariables 247 }

remoteStorageFileSystemUsageHighEvent OBJECT-TYPE
  SYNTAX OCTET STRING (SIZE(0..1000))
  MAX-ACCESS read-only
  STATUS current
  DESCRIPTION
    "Pure Flash Array  file system  usage is high"
  ::= { caEventVariables 248 }

nfsShareNotHealthyEvent OBJECT-TYPE
  SYNTAX OCTET STRING (SIZE(0..1000))
  MAX-ACCESS read-only
  STATUS current
  DESCRIPTION
    "NFS share  with disk ID  mounted to node  with ip  is not healthy"
  ::= { caEventVariables 249 }

scribeBackgroundOpsStallingEvent OBJECT-TYPE
  SYNTAX OCTET STRING (SIZE(0..1000))
  MAX-ACCESS read-only
  STATUS current
  DESCRIPTION
    "Background ops are running for a longer time than expected"
  ::= { caEventVariables 250 }

eSDiskUsageExceedsThresholdEvent OBJECT-TYPE
  SYNTAX OCTET STRING (SIZE(0..1000))
  MAX-ACCESS read-only
  STATUS current
  DESCRIPTION
    "ES indices size on disk  is exceeding threshold."
  ::= { caEventVariables 251 }

dnsServerUnassignedEvent OBJECT-TYPE
  SYNTAX OCTET STRING (SIZE(0..1000))
  MAX-ACCESS read-only
  STATUS current
  DESCRIPTION
    "DNS server is not assigned on node  with IP "
  ::= { caEventVariables 252 }

insufficientResourcesToLaunchSysSrvPodEvent OBJECT-TYPE
  SYNTAX OCTET STRING (SIZE(0..1000))
  MAX-ACCESS read-only
  STATUS current
  DESCRIPTION
    "Failed to launch system service pos for instance  at  Application"
  ::= { caEventVariables 253 }

userDefaultPasswordEvent OBJECT-TYPE
  SYNTAX OCTET STRING (SIZE(0..1000))
  MAX-ACCESS read-only
  STATUS current
  DESCRIPTION
    "Cluster  is using default password on node  with ip "
  ::= { caEventVariables 254 }

vMMigrationIdentifiedEvent OBJECT-TYPE
  SYNTAX OCTET STRING (SIZE(0..1000))
  MAX-ACCESS read-only
  STATUS current
  DESCRIPTION
    "Linked migrated VMs across vCenters."
  ::= { caEventVariables 255 }

wormChangeForGroupAlertEvent OBJECT-TYPE
  SYNTAX OCTET STRING (SIZE(0..1000))
  MAX-ACCESS read-only
  STATUS current
  DESCRIPTION
    "Cluster  is at potential security risk due to changes in  protection group settings"
  ::= { caEventVariables 256 }

wormChangeForPolicyAlertEvent OBJECT-TYPE
  SYNTAX OCTET STRING (SIZE(0..1000))
  MAX-ACCESS read-only
  STATUS current
  DESCRIPTION
    "Cluster  is at potential security risk due to changes in  policy settings"
  ::= { caEventVariables 257 }

inconsistentInterfaceGroupSpeedEvent OBJECT-TYPE
  SYNTAX OCTET STRING (SIZE(0..1000))
  MAX-ACCESS read-only
  STATUS current
  DESCRIPTION
    "Interface speed mismatch in a group."
  ::= { caEventVariables 258 }

atomNodeMemoryAboveThresholdEvent OBJECT-TYPE
  SYNTAX OCTET STRING (SIZE(0..1000))
  MAX-ACCESS read-only
  STATUS current
  DESCRIPTION
    "Atom node memory usage on  is above threshold(). Current memory, Max memory."
  ::= { caEventVariables 259 }

diskWithCorruptedPartitionTableEvent OBJECT-TYPE
  SYNTAX OCTET STRING (SIZE(0..1000))
  MAX-ACCESS read-only
  STATUS current
  DESCRIPTION
    "VM with disks has a corrupted MBR/GPT partition table."
  ::= { caEventVariables 260 }

remoteStorageDataIpUnreachableEvent OBJECT-TYPE
  SYNTAX OCTET STRING (SIZE(0..1000))
  MAX-ACCESS read-only
  STATUS current
  DESCRIPTION
    "Remote storage Data IP is unreachable."
  ::= { caEventVariables 261 }

nodeTcpOrphanConnectionsExceededEvent OBJECT-TYPE
  SYNTAX OCTET STRING (SIZE(0..1000))
  MAX-ACCESS read-only
  STATUS current
  DESCRIPTION
    "TCP orphan connections exceeded the threshold."
  ::= { caEventVariables 262 }

appNetworkMasterUnhealthyEvent OBJECT-TYPE
  SYNTAX OCTET STRING (SIZE(0..1000))
  MAX-ACCESS read-only
  STATUS current
  DESCRIPTION
    "App Network Master status is unhealthy"
  ::= { caEventVariables 263 }

appNetworkNodeUnhealthyEvent OBJECT-TYPE
  SYNTAX OCTET STRING (SIZE(0..1000))
  MAX-ACCESS read-only
  STATUS current
  DESCRIPTION
    "Node  App Network Node status is unhealthy"
  ::= { caEventVariables 264 }

lowReplicationFactorEvent OBJECT-TYPE
  SYNTAX OCTET STRING (SIZE(0..1000))
  MAX-ACCESS read-only
  STATUS current
  DESCRIPTION
    " cluster is on Replication Factor 1 There is no resiliency to handle disk failure!"
  ::= { caEventVariables 265 }

duplicateIpDetectedEvent OBJECT-TYPE
  SYNTAX OCTET STRING (SIZE(0..1000))
  MAX-ACCESS read-only
  STATUS current
  DESCRIPTION
    "Duplicate IP detected in  with ip "
  ::= { caEventVariables 266 }

powerSupplyAcRestoredEvent OBJECT-TYPE
  SYNTAX OCTET STRING (SIZE(0..1000))
  MAX-ACCESS read-only
  STATUS current
  DESCRIPTION
    "Power Supply Ac restored"
  ::= { caEventVariables 267 }

remoteClusterNotReachableEvent OBJECT-TYPE
  SYNTAX OCTET STRING (SIZE(0..1000))
  MAX-ACCESS read-only
  STATUS current
  DESCRIPTION
    "Remote cluster is not reachable from cluster."
  ::= { caEventVariables 268 }

remoteStorageUnexpectedNfsExportRulesEvent OBJECT-TYPE
  SYNTAX OCTET STRING (SIZE(0..1000))
  MAX-ACCESS read-only
  STATUS current
  DESCRIPTION
    "NFS export rule mismatch on Pure FlashBlade  file system "
  ::= { caEventVariables 269 }

unregisteredClusterEvent OBJECT-TYPE
  SYNTAX OCTET STRING (SIZE(0..1000))
  MAX-ACCESS read-only
  STATUS current
  DESCRIPTION
    "Cluster is unregistered."
  ::= { caEventVariables 270 }

clusterPendingAuditReportUploadEvent OBJECT-TYPE
  SYNTAX OCTET STRING (SIZE(0..1000))
  MAX-ACCESS read-only
  STATUS current
  DESCRIPTION
    "Audit report is due."
  ::= { caEventVariables 271 }

appNetworkResourceUnhealthyEvent OBJECT-TYPE
  SYNTAX OCTET STRING (SIZE(0..1000))
  MAX-ACCESS read-only
  STATUS current
  DESCRIPTION
    "App Network Resources status is unhealthy"
  ::= { caEventVariables 272 }

entityWithTooManyOpenHandlesEvent OBJECT-TYPE
  SYNTAX OCTET STRING (SIZE(0..1000))
  MAX-ACCESS read-only
  STATUS current
  DESCRIPTION
    "There are too many open handles for the same entity"
  ::= { caEventVariables 273 }

viewSlowProtocolOpEvent OBJECT-TYPE
  SYNTAX OCTET STRING (SIZE(0..1000))
  MAX-ACCESS read-only
  STATUS current
  DESCRIPTION
    "Slow operation detected from view"
  ::= { caEventVariables 274 }

policyDatalockDurationChangedEvent OBJECT-TYPE
  SYNTAX OCTET STRING (SIZE(0..1000))
  MAX-ACCESS read-only
  STATUS current
  DESCRIPTION
    "Protection policy datalock duration changed."
  ::= { caEventVariables 275 }

protectionPolicyModifiedEvent OBJECT-TYPE
  SYNTAX OCTET STRING (SIZE(0..1000))
  MAX-ACCESS read-only
  STATUS current
  DESCRIPTION
    "Protection policy modified."
  ::= { caEventVariables 276 }

protectionGroupModifiedEvent OBJECT-TYPE
  SYNTAX OCTET STRING (SIZE(0..1000))
  MAX-ACCESS read-only
  STATUS current
  DESCRIPTION
    "Protection group modified."
  ::= { caEventVariables 277 }

protectionRunModifiedEvent OBJECT-TYPE
  SYNTAX OCTET STRING (SIZE(0..1000))
  MAX-ACCESS read-only
  STATUS current
  DESCRIPTION
    "Protection run modified."
  ::= { caEventVariables 278 }

viewFailoverDuplicateViewUIDEvent OBJECT-TYPE
  SYNTAX OCTET STRING (SIZE(0..1000))
  MAX-ACCESS read-only
  STATUS current
  DESCRIPTION
    "Multiple views exist on the cluster with same universal view id"
  ::= { caEventVariables 279 }

viewFailoverReplicationFailedEvent OBJECT-TYPE
  SYNTAX OCTET STRING (SIZE(0..1000))
  MAX-ACCESS read-only
  STATUS current
  DESCRIPTION
    "Replication for planned failover of view  failed"
  ::= { caEventVariables 280 }

viewFailoverStuckEvent OBJECT-TYPE
  SYNTAX OCTET STRING (SIZE(0..1000))
  MAX-ACCESS read-only
  STATUS current
  DESCRIPTION
    "Planned failover of view  is stuck"
  ::= { caEventVariables 281 }

viewFailoverFailedEvent OBJECT-TYPE
  SYNTAX OCTET STRING (SIZE(0..1000))
  MAX-ACCESS read-only
  STATUS current
  DESCRIPTION
    "Unsuccessful failover of view "
  ::= { caEventVariables 282 }

viewFailoverStateUpdateFailedEvent OBJECT-TYPE
  SYNTAX OCTET STRING (SIZE(0..1000))
  MAX-ACCESS read-only
  STATUS current
  DESCRIPTION
    "Update of state maintained for failover of view  failed"
  ::= { caEventVariables 283 }

vaultConfigValidationFailedEvent OBJECT-TYPE
  SYNTAX OCTET STRING (SIZE(0..1000))
  MAX-ACCESS read-only
  STATUS current
  DESCRIPTION
    "Config validation failed for the vault."
  ::= { caEventVariables 284 }

remoteReplicationTrackingViewUpdateFailedEvent OBJECT-TYPE
  SYNTAX OCTET STRING (SIZE(0..1000))
  MAX-ACCESS read-only
  STATUS current
  DESCRIPTION
    "Update of tracking view for replication failed"
  ::= { caEventVariables 285 }

remoteIndexingFallbackEvent OBJECT-TYPE
  SYNTAX OCTET STRING (SIZE(0..1000))
  MAX-ACCESS read-only
  STATUS current
  DESCRIPTION
    "Remote indexing for volume has failed. Falling back to local indexing."
  ::= { caEventVariables 286 }

archiveObjectGCFailedAlertEvent OBJECT-TYPE
  SYNTAX OCTET STRING (SIZE(0..1000))
  MAX-ACCESS read-only
  STATUS current
  DESCRIPTION
    "Archive object  garbage collection in external target  failed."
  ::= { caEventVariables 287 }

highRPCLatenciesEvent OBJECT-TYPE
  SYNTAX OCTET STRING (SIZE(0..1000))
  MAX-ACCESS read-only
  STATUS current
  DESCRIPTION
    "RPC latencies for metadata service between node  and  are high, mean latency of  usecs has been observed. Latencies were measured over a  secs."
  ::= { caEventVariables 288 }

unexpectedIpAddressEvent OBJECT-TYPE
  SYNTAX OCTET STRING (SIZE(0..1000))
  MAX-ACCESS read-only
  STATUS current
  DESCRIPTION
    "Unexpected IP Address in an interface."
  ::= { caEventVariables 289 }

policyDatalockChangedEvent OBJECT-TYPE
  SYNTAX OCTET STRING (SIZE(0..1000))
  MAX-ACCESS read-only
  STATUS current
  DESCRIPTION
    "Datalock was  for policy  and  target"
  ::= { caEventVariables 290 }

protectionGroupDeletedEvent OBJECT-TYPE
  SYNTAX OCTET STRING (SIZE(0..1000))
  MAX-ACCESS read-only
  STATUS current
  DESCRIPTION
    "Protection Group was deleted"
  ::= { caEventVariables 291 }

sourceConnectivityFailureEvent OBJECT-TYPE
  SYNTAX OCTET STRING (SIZE(0..1000))
  MAX-ACCESS read-only
  STATUS current
  DESCRIPTION
    "Failure in source connectivity verification."
  ::= { caEventVariables 292 }

diskOkToRemoveEvent OBJECT-TYPE
  SYNTAX OCTET STRING (SIZE(0..1000))
  MAX-ACCESS read-only
  STATUS current
  DESCRIPTION
    "Disk is OK to remove."
  ::= { caEventVariables 293 }

systemServiceAppInstallationFailedEvent OBJECT-TYPE
  SYNTAX OCTET STRING (SIZE(0..1000))
  MAX-ACCESS read-only
  STATUS current
  DESCRIPTION
    "Failed to install System service"
  ::= { caEventVariables 294 }

nexusFaultIsolationRecoveryEvent OBJECT-TYPE
  SYNTAX OCTET STRING (SIZE(0..1000))
  MAX-ACCESS read-only
  STATUS current
  DESCRIPTION
    "Nexus executing recovery actions."
  ::= { caEventVariables 295 }

continuousDataProtectionAlertEvent OBJECT-TYPE
  SYNTAX OCTET STRING (SIZE(0..1000))
  MAX-ACCESS read-only
  STATUS current
  DESCRIPTION
    "Alert is raised for CDP VM entity, Protection Group ID"
  ::= { caEventVariables 296 }

hostShellAccessExpiryEvent OBJECT-TYPE
  SYNTAX OCTET STRING (SIZE(0..1000))
  MAX-ACCESS read-only
  STATUS current
  DESCRIPTION
    "Host shell access is about to expire"
  ::= { caEventVariables 297 }

bucketMetadataModifiedEvent OBJECT-TYPE
  SYNTAX OCTET STRING (SIZE(0..1000))
  MAX-ACCESS read-only
  STATUS current
  DESCRIPTION
    "Metadata  of  view  modified"
  ::= { caEventVariables 298 }

bucketACLUpdatedEvent OBJECT-TYPE
  SYNTAX OCTET STRING (SIZE(0..1000))
  MAX-ACCESS read-only
  STATUS current
  DESCRIPTION
    "Access Control List of S3 view  updated"
  ::= { caEventVariables 299 }

bucketCreatedEvent OBJECT-TYPE
  SYNTAX OCTET STRING (SIZE(0..1000))
  MAX-ACCESS read-only
  STATUS current
  DESCRIPTION
    "New  view with name  is created"
  ::= { caEventVariables 300 }

bucketDeletedEvent OBJECT-TYPE
  SYNTAX OCTET STRING (SIZE(0..1000))
  MAX-ACCESS read-only
  STATUS current
  DESCRIPTION
    " view with name  is deleted"
  ::= { caEventVariables 301 }

serviceGflagsChangedEvent OBJECT-TYPE
  SYNTAX OCTET STRING (SIZE(0..1000))
  MAX-ACCESS read-only
  STATUS current
  DESCRIPTION
    "Service gflags changed notification."
  ::= { caEventVariables 302 }

algorithmFrequentlyTimeOutAlertEvent OBJECT-TYPE
  SYNTAX OCTET STRING (SIZE(0..1000))
  MAX-ACCESS read-only
  STATUS current
  DESCRIPTION
    "An algorithm is frequently timing out and is behind schedule for a long time."
  ::= { caEventVariables 303 }

successfulFailoverOpAlertEvent OBJECT-TYPE
  SYNTAX OCTET STRING (SIZE(0..1000))
  MAX-ACCESS read-only
  STATUS current
  DESCRIPTION
    "Failover operation triggered from cluster  using runbook  is successful."
  ::= { caEventVariables 304 }

successfulFailbackOpAlertEvent OBJECT-TYPE
  SYNTAX OCTET STRING (SIZE(0..1000))
  MAX-ACCESS read-only
  STATUS current
  DESCRIPTION
    "Failback operation triggered from cluster  using runbook  is successful."
  ::= { caEventVariables 305 }

successfulTestAndDevOpAlertEvent OBJECT-TYPE
  SYNTAX OCTET STRING (SIZE(0..1000))
  MAX-ACCESS read-only
  STATUS current
  DESCRIPTION
    "Test and Dev operation triggered from cluster  using runbook  is successful."
  ::= { caEventVariables 306 }

successfulPrepareFailbackOpAlertEvent OBJECT-TYPE
  SYNTAX OCTET STRING (SIZE(0..1000))
  MAX-ACCESS read-only
  STATUS current
  DESCRIPTION
    "Prepare failback operation triggered from cluster  using runbook  is successful."
  ::= { caEventVariables 307 }

successfulTeardownOpAlertEvent OBJECT-TYPE
  SYNTAX OCTET STRING (SIZE(0..1000))
  MAX-ACCESS read-only
  STATUS current
  DESCRIPTION
    "Teardown operation triggered from cluster  using runbook  is successful."
  ::= { caEventVariables 308 }

failedFailoverOpAlertEvent OBJECT-TYPE
  SYNTAX OCTET STRING (SIZE(0..1000))
  MAX-ACCESS read-only
  STATUS current
  DESCRIPTION
    "Failover operation triggered from cluster  using runbook  has failed."
  ::= { caEventVariables 309 }

failedFailbackOpAlertEvent OBJECT-TYPE
  SYNTAX OCTET STRING (SIZE(0..1000))
  MAX-ACCESS read-only
  STATUS current
  DESCRIPTION
    "Failback operation triggered from cluster  using runbook  has failed."
  ::= { caEventVariables 310 }

failedTestAndDevOpAlertEvent OBJECT-TYPE
  SYNTAX OCTET STRING (SIZE(0..1000))
  MAX-ACCESS read-only
  STATUS current
  DESCRIPTION
    "Test and Dev operation triggered from cluster  using runbook  has failed."
  ::= { caEventVariables 311 }

failedPrepareFailbackOpAlertEvent OBJECT-TYPE
  SYNTAX OCTET STRING (SIZE(0..1000))
  MAX-ACCESS read-only
  STATUS current
  DESCRIPTION
    "Prepare failback operation triggered from cluster  using runbook  has failed."
  ::= { caEventVariables 312 }

failedTeardownOpAlertEvent OBJECT-TYPE
  SYNTAX OCTET STRING (SIZE(0..1000))
  MAX-ACCESS read-only
  STATUS current
  DESCRIPTION
    "Teardown operation triggered from cluster  using runbook  has failed."
  ::= { caEventVariables 313 }

ssdMediaErrorEvent OBJECT-TYPE
  SYNTAX OCTET STRING (SIZE(0..1000))
  MAX-ACCESS read-only
  STATUS current
  DESCRIPTION
    "Ssd Media Error"
  ::= { caEventVariables 314 }

diskNeedFirmwareUpgradeEvent OBJECT-TYPE
  SYNTAX OCTET STRING (SIZE(0..1000))
  MAX-ACCESS read-only
  STATUS current
  DESCRIPTION
    "Disk ID  needs firmware upgrade on the node  with ip ."
  ::= { caEventVariables 315 }

metadataMovedToFlashbladeEvent OBJECT-TYPE
  SYNTAX OCTET STRING (SIZE(0..1000))
  MAX-ACCESS read-only
  STATUS current
  DESCRIPTION
    "All the metadata has moved to the flashblade."
  ::= { caEventVariables 316 }

viewCloneMetadataBloatEvent OBJECT-TYPE
  SYNTAX OCTET STRING (SIZE(0..1000))
  MAX-ACCESS read-only
  STATUS current
  DESCRIPTION
    "Too many unflushed records in metadata data journal for  during cloning"
  ::= { caEventVariables 317 }

chunkFileContainerInconsistencyEvent OBJECT-TYPE
  SYNTAX OCTET STRING (SIZE(0..1000))
  MAX-ACCESS read-only
  STATUS current
  DESCRIPTION
    "Chunk File Container inconsistency, cluster internal error that requires action by Cohesity Support"
  ::= { caEventVariables 318 }

apolloIssuedActionVersionMismatchEvent OBJECT-TYPE
  SYNTAX OCTET STRING (SIZE(0..1000))
  MAX-ACCESS read-only
  STATUS current
  DESCRIPTION
    "Apollo is issuing action(s) with API version . Action was ignored by bridge since it expects an API version of ."
  ::= { caEventVariables 319 }

networkStatsIsNotNormalEvent OBJECT-TYPE
  SYNTAX OCTET STRING (SIZE(0..1000))
  MAX-ACCESS read-only
  STATUS current
  DESCRIPTION
    "Node  with ip  netstats is not normal."
  ::= { caEventVariables 320 }

highClusterUtilizationEvent OBJECT-TYPE
  SYNTAX OCTET STRING (SIZE(0..1000))
  MAX-ACCESS read-only
  STATUS current
  DESCRIPTION
    "Cluster utilization is high (>=85%)."
  ::= { caEventVariables 321 }

createSnapshotSucceededEvent OBJECT-TYPE
  SYNTAX OCTET STRING (SIZE(0..1000))
  MAX-ACCESS read-only
  STATUS current
  DESCRIPTION
    "Create Snapshot version  succeeded on the cluster"
  ::= { caEventVariables 322 }

nodeConnectivityFailedEvent OBJECT-TYPE
  SYNTAX OCTET STRING (SIZE(0..1000))
  MAX-ACCESS read-only
  STATUS current
  DESCRIPTION
    "Node  with IP  connection failure to ."
  ::= { caEventVariables 323 }

deferScheduleEvent OBJECT-TYPE
  SYNTAX OCTET STRING (SIZE(0..1000))
  MAX-ACCESS read-only
  STATUS current
  DESCRIPTION
    "Deferred schedule for  to resolve conflicts among multiple schedules for  with id "
  ::= { caEventVariables 324 }

cloudDataOpFailureEvent OBJECT-TYPE
  SYNTAX OCTET STRING (SIZE(0..1000))
  MAX-ACCESS read-only
  STATUS current
  DESCRIPTION
    "Cloud operation failures detected on external target "
  ::= { caEventVariables 325 }

objectStorePortalInitializationFailureEvent OBJECT-TYPE
  SYNTAX OCTET STRING (SIZE(0..1000))
  MAX-ACCESS read-only
  STATUS current
  DESCRIPTION
    "Bridge S3 Http Server failed to initialize with reason "
  ::= { caEventVariables 326 }

kubernetesObjectsCleanupAlertEvent OBJECT-TYPE
  SYNTAX OCTET STRING (SIZE(0..1000))
  MAX-ACCESS read-only
  STATUS current
  DESCRIPTION
    "Failed to cleanup kubernetes objects on stale incarnation id"
  ::= { caEventVariables 327 }

nodeNotPresentInKubernetesClusterEvent OBJECT-TYPE
  SYNTAX OCTET STRING (SIZE(0..1000))
  MAX-ACCESS read-only
  STATUS current
  DESCRIPTION
    "Node(s) [  ] are not part of kubernetes cluster"
  ::= { caEventVariables 328 }

objectDeletionRejectedEvent OBJECT-TYPE
  SYNTAX OCTET STRING (SIZE(0..1000))
  MAX-ACCESS read-only
  STATUS current
  DESCRIPTION
    "Could not delete objects in the run before run expiry. They will be deleted when the run snapshot is expired. Protection Group ID. Backup Type. Run id."
  ::= { caEventVariables 329 }

rpmPackageVersionMismatchedEvent OBJECT-TYPE
  SYNTAX OCTET STRING (SIZE(0..1000))
  MAX-ACCESS read-only
  STATUS current
  DESCRIPTION
    "Rpm package version mismatched on the node  with ip "
  ::= { caEventVariables 330 }

baseOSVersionMismatchedEvent OBJECT-TYPE
  SYNTAX OCTET STRING (SIZE(0..1000))
  MAX-ACCESS read-only
  STATUS current
  DESCRIPTION
    "BaseOS version mismatched on the node  with ip "
  ::= { caEventVariables 331 }

createSnapshotFailedEvent OBJECT-TYPE
  SYNTAX OCTET STRING (SIZE(0..1000))
  MAX-ACCESS read-only
  STATUS current
  DESCRIPTION
    "Create Snapshot version  failed on the cluster"
  ::= { caEventVariables 332 }

restoreSnapshotStartedEvent OBJECT-TYPE
  SYNTAX OCTET STRING (SIZE(0..1000))
  MAX-ACCESS read-only
  STATUS current
  DESCRIPTION
    "Restore Snapshot version  started on the cluster"
  ::= { caEventVariables 333 }

restoreSnapshotSucceededEvent OBJECT-TYPE
  SYNTAX OCTET STRING (SIZE(0..1000))
  MAX-ACCESS read-only
  STATUS current
  DESCRIPTION
    "Restore Snapshot version  succeeded on the cluster"
  ::= { caEventVariables 334 }

restoreSnapshotFailedEvent OBJECT-TYPE
  SYNTAX OCTET STRING (SIZE(0..1000))
  MAX-ACCESS read-only
  STATUS current
  DESCRIPTION
    "Restore Snapshot version  failed on the cluster"
  ::= { caEventVariables 335 }

createSnapshotStartedEvent OBJECT-TYPE
  SYNTAX OCTET STRING (SIZE(0..1000))
  MAX-ACCESS read-only
  STATUS current
  DESCRIPTION
    "Create Snapshot version  started on the cluster"
  ::= { caEventVariables 336 }

principalWithNonViewerRoleEvent OBJECT-TYPE
  SYNTAX OCTET STRING (SIZE(0..1000))
  MAX-ACCESS read-only
  STATUS current
  DESCRIPTION
    " cluster has one or more iris principals with roles other than viewer"
  ::= { caEventVariables 337 }

azureCEHostCachingEnabledEvent OBJECT-TYPE
  SYNTAX OCTET STRING (SIZE(0..1000))
  MAX-ACCESS read-only
  STATUS current
  DESCRIPTION
    "In case of Azure Cloud Edition clusters if Host Caching is not set to 'None' on Azure nodes/VMs then it might lead to potential data loss. Disks that have Host caching not set to 'None' are on node"
  ::= { caEventVariables 338 }

recentLogBeingRotatedEvent OBJECT-TYPE
  SYNTAX OCTET STRING (SIZE(0..1000))
  MAX-ACCESS read-only
  STATUS current
  DESCRIPTION
    " log in  hours rotated on node  "
  ::= { caEventVariables 339 }

repeatedlyFailingShardAlertEvent OBJECT-TYPE
  SYNTAX OCTET STRING (SIZE(0..1000))
  MAX-ACCESS read-only
  STATUS current
  DESCRIPTION
    "Background tasks have hit a slowness issue because Apollo shards are failing more often than expected."
  ::= { caEventVariables 340 }

backlogDuringBlackOutEvent OBJECT-TYPE
  SYNTAX OCTET STRING (SIZE(0..1000))
  MAX-ACCESS read-only
  STATUS current
  DESCRIPTION
    "Apollo is in backlog state for more than a threshold number of days during the blackout window auto-scheduling."
  ::= { caEventVariables 341 }

timeConsumingShardAlertEvent OBJECT-TYPE
  SYNTAX OCTET STRING (SIZE(0..1000))
  MAX-ACCESS read-only
  STATUS current
  DESCRIPTION
    "Apollo shard runtime is greater than the average value by a threshold."
  ::= { caEventVariables 342 }

highNonDedupToDedupPercentEvent OBJECT-TYPE
  SYNTAX OCTET STRING (SIZE(0..1000))
  MAX-ACCESS read-only
  STATUS current
  DESCRIPTION
    "High non-dedup to dedup percent observed in inline dedup Storage domain . This could lead to higher than expected cluster space usage."
  ::= { caEventVariables 343 }

appsModeDisabledDueToSubnetClashEvent OBJECT-TYPE
  SYNTAX OCTET STRING (SIZE(0..1000))
  MAX-ACCESS read-only
  STATUS current
  DESCRIPTION
    "Apps mode & Marketplace apps mode are disabled due to a subnet clash. To fix, update new subnet for apps, through edit cluster settings page(Settings->Summary->Configure->Configure Apps management network). Also enable marketplace apps mode if needed."
  ::= { caEventVariables 344 }

oracleMountFailureEvent OBJECT-TYPE
  SYNTAX OCTET STRING (SIZE(0..1000))
  MAX-ACCESS read-only
  STATUS current
  DESCRIPTION
    "If there are some mount failures, it will affect the backup/restore performance. Mount could fail because of many reasons like stale mount, incorrect mount options, e.t.c"
  ::= { caEventVariables 345 }

protectionServiceNotInitializedEvent OBJECT-TYPE
  SYNTAX OCTET STRING (SIZE(0..1000))
  MAX-ACCESS read-only
  STATUS current
  DESCRIPTION
    "Protection Service is not initialized"
  ::= { caEventVariables 346 }

fragmentActionsRepeatedlyFailingAlertEvent OBJECT-TYPE
  SYNTAX OCTET STRING (SIZE(0..1000))
  MAX-ACCESS read-only
  STATUS current
  DESCRIPTION
    "Many background actions in Apollo are hitting unexpected errors."
  ::= { caEventVariables 347 }

userTuningsStuckAlertIdEvent OBJECT-TYPE
  SYNTAX OCTET STRING (SIZE(0..1000))
  MAX-ACCESS read-only
  STATUS current
  DESCRIPTION
    "User tuned gflags are not set/cleared on time."
  ::= { caEventVariables 348 }

kBrickMetadataInconsistentStateEvent OBJECT-TYPE
  SYNTAX OCTET STRING (SIZE(0..1000))
  MAX-ACCESS read-only
  STATUS current
  DESCRIPTION
    "Chunk mapping for chunk  in brick with leaf node id  is in inconsistent state"
  ::= { caEventVariables 349 }

eCConversionBackloggedEvent OBJECT-TYPE
  SYNTAX OCTET STRING (SIZE(0..1000))
  MAX-ACCESS read-only
  STATUS current
  DESCRIPTION
    "Old un-encoded chunk file  observed in Storage domain . Erasure coding algorithm is backlogged. This could lead to higher than expected cluster space usage."
  ::= { caEventVariables 350 }

diskSwappedEvent OBJECT-TYPE
  SYNTAX OCTET STRING (SIZE(0..1000))
  MAX-ACCESS read-only
  STATUS current
  DESCRIPTION
    "Disk with id  and serial  on node  with ip  is swapped from node "
  ::= { caEventVariables 351 }

remoteStorageConfigureFailedEvent OBJECT-TYPE
  SYNTAX OCTET STRING (SIZE(0..1000))
  MAX-ACCESS read-only
  STATUS current
  DESCRIPTION
    "Failed to configure remote storage"
  ::= { caEventVariables 352 }

aVHighRequestQueueSizeEvent OBJECT-TYPE
  SYNTAX OCTET STRING (SIZE(0..1000))
  MAX-ACCESS read-only
  STATUS current
  DESCRIPTION
    "Antivirus scan queue is too long"
  ::= { caEventVariables 353 }

aVHighResponseTimeEvent OBJECT-TYPE
  SYNTAX OCTET STRING (SIZE(0..1000))
  MAX-ACCESS read-only
  STATUS current
  DESCRIPTION
    "Antivirus scan slowness is detected"
  ::= { caEventVariables 354 }

orphanEntityValueVersionMismatchEvent OBJECT-TYPE
  SYNTAX OCTET STRING (SIZE(0..1000))
  MAX-ACCESS read-only
  STATUS current
  DESCRIPTION
    "Cluster  might have an error that requires action by Cohesity Support"
  ::= { caEventVariables 355 }

heavyFileOperationContentionEvent OBJECT-TYPE
  SYNTAX OCTET STRING (SIZE(0..1000))
  MAX-ACCESS read-only
  STATUS current
  DESCRIPTION
    "Operation on the same file has been too heavy and rejected"
  ::= { caEventVariables 356 }

verifyNonExistentBrickFailedEvent OBJECT-TYPE
  SYNTAX OCTET STRING (SIZE(0..1000))
  MAX-ACCESS read-only
  STATUS current
  DESCRIPTION
    "Verify Non Existent Brick failed, cluster internal error that requires action by Cohesity Support"
  ::= { caEventVariables 357 }

chunkMigrationVerifyChunkInCfmFailedEvent OBJECT-TYPE
  SYNTAX OCTET STRING (SIZE(0..1000))
  MAX-ACCESS read-only
  STATUS current
  DESCRIPTION
    "Chunk Migration failed, cluster internal error that requires action by Cohesity Support"
  ::= { caEventVariables 358 }

chunkMigrationVerifyBrickOwnedNDDChunksFailedEvent OBJECT-TYPE
  SYNTAX OCTET STRING (SIZE(0..1000))
  MAX-ACCESS read-only
  STATUS current
  DESCRIPTION
    "Chunk Migration failed, cluster internal error that requires action by Cohesity Support"
  ::= { caEventVariables 359 }

gCStalledAlertEvent OBJECT-TYPE
  SYNTAX OCTET STRING (SIZE(0..1000))
  MAX-ACCESS read-only
  STATUS current
  DESCRIPTION
    "Garbage collection has stalled on the cluster. Please contact customer support immediately. If corrective action is not taken, the cluster will run out of space causing an outage."
  ::= { caEventVariables 360 }

upgradeCancelledEvent OBJECT-TYPE
  SYNTAX OCTET STRING (SIZE(0..1000))
  MAX-ACCESS read-only
  STATUS current
  DESCRIPTION
    "Upgrade to target version  canceled from the node  with ip "
  ::= { caEventVariables 361 }

oracleRestoreChainBreakEvent OBJECT-TYPE
  SYNTAX OCTET STRING (SIZE(0..1000))
  MAX-ACCESS read-only
  STATUS current
  DESCRIPTION
    "Oracle Restore Chain Break."
  ::= { caEventVariables 362 }

nasSourceSnapshotDeletionFailedEvent OBJECT-TYPE
  SYNTAX OCTET STRING (SIZE(0..1000))
  MAX-ACCESS read-only
  STATUS current
  DESCRIPTION
    "Deletion of NAS source's native snapshot failed. This was created by Cohesity to perform backup, please delete it as it is not required anymore."
  ::= { caEventVariables 363 }

isilonChangelistCleanupFailedEvent OBJECT-TYPE
  SYNTAX OCTET STRING (SIZE(0..1000))
  MAX-ACCESS read-only
  STATUS current
  DESCRIPTION
    "Deletion of the cohesity created changelist failed, most likely due to transient errors. This was created by Cohesity to perform backup, please delete it as it is not required anymore."
  ::= { caEventVariables 364 }

nodeRemovalStuckEvent OBJECT-TYPE
  SYNTAX OCTET STRING (SIZE(0..1000))
  MAX-ACCESS read-only
  STATUS current
  DESCRIPTION
    "Removal is stuck for Node with id"
  ::= { caEventVariables 365 }

diskRemovalStuckEvent OBJECT-TYPE
  SYNTAX OCTET STRING (SIZE(0..1000))
  MAX-ACCESS read-only
  STATUS current
  DESCRIPTION
    "Removal is stuck for Disk with id"
  ::= { caEventVariables 366 }

kMSFailoverEvent OBJECT-TYPE
  SYNTAX OCTET STRING (SIZE(0..1000))
  MAX-ACCESS read-only
  STATUS current
  DESCRIPTION
    "KMS  with version  in cluster  has failed over to backup server"
  ::= { caEventVariables 367 }

restoreTaskWarningEvent OBJECT-TYPE
  SYNTAX OCTET STRING (SIZE(0..1000))
  MAX-ACCESS read-only
  STATUS current
  DESCRIPTION
    "Restore for object  in job  succeeded with warnings"
  ::= { caEventVariables 368 }

restoreTaskFailedEvent OBJECT-TYPE
  SYNTAX OCTET STRING (SIZE(0..1000))
  MAX-ACCESS read-only
  STATUS current
  DESCRIPTION
    "Restore for object  in job  failed"
  ::= { caEventVariables 369 }

overwriteThrottlingScheduleAlertEvent OBJECT-TYPE
  SYNTAX OCTET STRING (SIZE(0..1000))
  MAX-ACCESS read-only
  STATUS current
  DESCRIPTION
    "A backlog in background clean up task was observed. Once cluster utilization becomes high, its priority will be increased which could create delays in the SmartFiles workloads. Kindly contact Cohesity support in case such delays in the SmartFiles workloads are experienced."
  ::= { caEventVariables 370 }

uIUserLockoutEvent OBJECT-TYPE
  SYNTAX OCTET STRING (SIZE(0..1000))
  MAX-ACCESS read-only
  STATUS current
  DESCRIPTION
    "UI User Locked out"
  ::= { caEventVariables 371 }

uILoginFailureEvent OBJECT-TYPE
  SYNTAX OCTET STRING (SIZE(0..1000))
  MAX-ACCESS read-only
  STATUS current
  DESCRIPTION
    "UI Login failed"
  ::= { caEventVariables 372 }

uILoginSuccessEvent OBJECT-TYPE
  SYNTAX OCTET STRING (SIZE(0..1000))
  MAX-ACCESS read-only
  STATUS current
  DESCRIPTION
    "UI Login is successful"
  ::= { caEventVariables 373 }

inactivityUITimeoutChangedEvent OBJECT-TYPE
  SYNTAX OCTET STRING (SIZE(0..1000))
  MAX-ACCESS read-only
  STATUS current
  DESCRIPTION
    "UI Inactivity Timeout Changed"
  ::= { caEventVariables 374 }

absoluteUITimeoutChangedEvent OBJECT-TYPE
  SYNTAX OCTET STRING (SIZE(0..1000))
  MAX-ACCESS read-only
  STATUS current
  DESCRIPTION
    "UI Absolute Timeout Changed"
  ::= { caEventVariables 375 }

sSHLoginSuccessEvent OBJECT-TYPE
  SYNTAX OCTET STRING (SIZE(0..1000))
  MAX-ACCESS read-only
  STATUS current
  DESCRIPTION
    "UI Login is successful"
  ::= { caEventVariables 376 }

sSHLoginFailureEvent OBJECT-TYPE
  SYNTAX OCTET STRING (SIZE(0..1000))
  MAX-ACCESS read-only
  STATUS current
  DESCRIPTION
    "UI Login failed"
  ::= { caEventVariables 377 }

clusterServicesManuallyStoppedEvent OBJECT-TYPE
  SYNTAX OCTET STRING (SIZE(0..1000))
  MAX-ACCESS read-only
  STATUS current
  DESCRIPTION
    "Cluster Services Manually Stopped."
  ::= { caEventVariables 378 }

clusterServicesManuallyStartedEvent OBJECT-TYPE
  SYNTAX OCTET STRING (SIZE(0..1000))
  MAX-ACCESS read-only
  STATUS current
  DESCRIPTION
    "Cluster Services Manually Started."
  ::= { caEventVariables 379 }

cloneBackupCleanupIssuesEvent OBJECT-TYPE
  SYNTAX OCTET STRING (SIZE(0..1000))
  MAX-ACCESS read-only
  STATUS current
  DESCRIPTION
    "Cleanup for clone backup dir  has failed."
  ::= { caEventVariables 380 }

tenantIndexingConfigMissingEvent OBJECT-TYPE
  SYNTAX OCTET STRING (SIZE(0..1000))
  MAX-ACCESS read-only
  STATUS current
  DESCRIPTION
    "Tenant Indexing cloud config is missing."
  ::= { caEventVariables 381 }

staleDirsFoundInYodaCloneBackupViewsEvent OBJECT-TYPE
  SYNTAX OCTET STRING (SIZE(0..1000))
  MAX-ACCESS read-only
  STATUS current
  DESCRIPTION
    "Manual cleanup of yoda clone backup views is needed to improve indexing speed."
  ::= { caEventVariables 382 }

archiveValidationFailedAlertEvent OBJECT-TYPE
  SYNTAX OCTET STRING (SIZE(0..1000))
  MAX-ACCESS read-only
  STATUS current
  DESCRIPTION
    "Cohesity has determined an inconsistency in an archive created on the external target "
  ::= { caEventVariables 383 }

remoteReplicationEncryptionKeyMismatchEvent OBJECT-TYPE
  SYNTAX OCTET STRING (SIZE(0..1000))
  MAX-ACCESS read-only
  STATUS current
  DESCRIPTION
    "Mismatch in encryption key for replication to remote cluster "
  ::= { caEventVariables 384 }

morphedGarbageThresholdExceededAlertEvent OBJECT-TYPE
  SYNTAX OCTET STRING (SIZE(0..1000))
  MAX-ACCESS read-only
  STATUS current
  DESCRIPTION
    "Imbalance threshold exceeded for chunkfiles in cluster , partition , This can cause increase in the cluster usage"
  ::= { caEventVariables 385 }

switchedToSpaceModeEvent OBJECT-TYPE
  SYNTAX OCTET STRING (SIZE(0..1000))
  MAX-ACCESS read-only
  STATUS current
  DESCRIPTION
    "Metadata is moving to space conserve mode. This may have a significantly adverse effect on performance. Please add more metadata space for better performance."
  ::= { caEventVariables 386 }

imbalanceThresholdExceededAlertEvent OBJECT-TYPE
  SYNTAX OCTET STRING (SIZE(0..1000))
  MAX-ACCESS read-only
  STATUS current
  DESCRIPTION
    "Imbalance threshold exceeded for chunkfiles in cluster , partition , This can cause increase in the cluster usage"
  ::= { caEventVariables 387 }

possibleMetadataInconsistencyEvent OBJECT-TYPE
  SYNTAX OCTET STRING (SIZE(0..1000))
  MAX-ACCESS read-only
  STATUS current
  DESCRIPTION
    "Cohesity alert notification."
  ::= { caEventVariables 388 }

awsESIndexingErrorsEvent OBJECT-TYPE
  SYNTAX OCTET STRING (SIZE(0..1000))
  MAX-ACCESS read-only
  STATUS current
  DESCRIPTION
    "Cohesity alert notification."
  ::= { caEventVariables 389 }

corruptMFTErrorEvent OBJECT-TYPE
  SYNTAX OCTET STRING (SIZE(0..1000))
  MAX-ACCESS read-only
  STATUS current
  DESCRIPTION
    "Cohesity alert notification."
  ::= { caEventVariables 390 }

protectionGroupWarningEvent OBJECT-TYPE
  SYNTAX OCTET STRING (SIZE(0..1000))
  MAX-ACCESS read-only
  STATUS current
  DESCRIPTION
    "Cohesity alert notification."
  ::= { caEventVariables 391 }

magnetoUnableToReachYodaEvent OBJECT-TYPE
  SYNTAX OCTET STRING (SIZE(0..1000))
  MAX-ACCESS read-only
  STATUS current
  DESCRIPTION
    "Protection service is unable to contact indexing service"
  ::= { caEventVariables 392 }

secureShellEnabledEvent OBJECT-TYPE
  SYNTAX OCTET STRING (SIZE(0..1000))
  MAX-ACCESS read-only
  STATUS current
  DESCRIPTION
    "Secure shell enabled."
  ::= { caEventVariables 393 }

secureShellDisabledEvent OBJECT-TYPE
  SYNTAX OCTET STRING (SIZE(0..1000))
  MAX-ACCESS read-only
  STATUS current
  DESCRIPTION
    "Secure shell disabled."
  ::= { caEventVariables 394 }

protectionRunExpiringEvent OBJECT-TYPE
  SYNTAX OCTET STRING (SIZE(0..1000))
  MAX-ACCESS read-only
  STATUS current
  DESCRIPTION
    "Protection Run close to expiry and having one or more failed copies."
  ::= { caEventVariables 395 }

vipPingFailedEvent OBJECT-TYPE
  SYNTAX OCTET STRING (SIZE(0..1000))
  MAX-ACCESS read-only
  STATUS current
  DESCRIPTION
    "Cohesity alert notification."
  ::= { caEventVariables 396 }

oracleUnresponsiveProgressQueryEvent OBJECT-TYPE
  SYNTAX OCTET STRING (SIZE(0..1000))
  MAX-ACCESS read-only
  STATUS current
  DESCRIPTION
    "Cohesity alert notification."
  ::= { caEventVariables 397 }

abacServerNotReachableEvent OBJECT-TYPE
  SYNTAX OCTET STRING (SIZE(0..1000))
  MAX-ACCESS read-only
  STATUS current
  DESCRIPTION
    "S3 ABAC server is not reachable."
  ::= { caEventVariables 398 }

abacServerCertExpiredEvent OBJECT-TYPE
  SYNTAX OCTET STRING (SIZE(0..1000))
  MAX-ACCESS read-only
  STATUS current
  DESCRIPTION
    "S3 ABAC server certificate has expired."
  ::= { caEventVariables 399 }

failedToChangeAuthForBackupViewEvent OBJECT-TYPE
  SYNTAX OCTET STRING (SIZE(0..1000))
  MAX-ACCESS read-only
  STATUS current
  DESCRIPTION
    "Failed to set / unset service auth config for some backup views."
  ::= { caEventVariables 400 }

agentCertIsAboutToExpireEvent OBJECT-TYPE
  SYNTAX OCTET STRING (SIZE(0..1000))
  MAX-ACCESS read-only
  STATUS current
  DESCRIPTION
    "Agent certificate is about to expire."
  ::= { caEventVariables 401 }

replicationHandshakeStuckEvent OBJECT-TYPE
  SYNTAX OCTET STRING (SIZE(0..1000))
  MAX-ACCESS read-only
  STATUS current
  DESCRIPTION
    "Handshake between the local and the remote cluster is stuck for the replication."
  ::= { caEventVariables 402 }

highUnreclaimedGarbageAlertEvent OBJECT-TYPE
  SYNTAX OCTET STRING (SIZE(0..1000))
  MAX-ACCESS read-only
  STATUS current
  DESCRIPTION
    "Critically high amount of unclaimed garbage has been detected on the cluster."
  ::= { caEventVariables 403 }

certificateIsAboutToExpireEvent OBJECT-TYPE
  SYNTAX OCTET STRING (SIZE(0..1000))
  MAX-ACCESS read-only
  STATUS current
  DESCRIPTION
    "Certificate is about to expire alert notification."
  ::= { caEventVariables 404 }

clockSkewBetweenClusterAndDCEvent OBJECT-TYPE
  SYNTAX OCTET STRING (SIZE(0..1000))
  MAX-ACCESS read-only
  STATUS current
  DESCRIPTION
    "There's a big clock skew between Cohesity cluster and Domain Controller. Will fail the authentication with this DC."
  ::= { caEventVariables 405 }

insecureClientDetectedEvent OBJECT-TYPE
  SYNTAX OCTET STRING (SIZE(0..1000))
  MAX-ACCESS read-only
  STATUS current
  DESCRIPTION
    "External client not using mTSL to connect to Cohesity cluster."
  ::= { caEventVariables 406 }

teamsPublicChannelsIndexingAlertEvent OBJECT-TYPE
  SYNTAX OCTET STRING (SIZE(0..1000))
  MAX-ACCESS read-only
  STATUS current
  DESCRIPTION
    "Indexing of public channels for an O365 Team is skipped as it has high number of public channels. This is an informative alert, not any failure. Please contact support team or refer to KB for details."
  ::= { caEventVariables 407 }

knownIssueDetectedAlertEvent OBJECT-TYPE
  SYNTAX OCTET STRING (SIZE(0..1000))
  MAX-ACCESS read-only
  STATUS current
  DESCRIPTION
    "Cohesity alert notification."
  ::= { caEventVariables 408 }

knownIssueDetectedCommandEvent OBJECT-TYPE
  SYNTAX OCTET STRING (SIZE(0..1000))
  MAX-ACCESS read-only
  STATUS current
  DESCRIPTION
    "Cohesity alert notification."
  ::= { caEventVariables 409 }

knownIssueDetectedGflagEvent OBJECT-TYPE
  SYNTAX OCTET STRING (SIZE(0..1000))
  MAX-ACCESS read-only
  STATUS current
  DESCRIPTION
    "Cohesity alert notification."
  ::= { caEventVariables 410 }

knownIssueDetectedPatchEvent OBJECT-TYPE
  SYNTAX OCTET STRING (SIZE(0..1000))
  MAX-ACCESS read-only
  STATUS current
  DESCRIPTION
    "Cohesity alert notification."
  ::= { caEventVariables 411 }

importantAwarenessCommunicationEvent OBJECT-TYPE
  SYNTAX OCTET STRING (SIZE(0..1000))
  MAX-ACCESS read-only
  STATUS current
  DESCRIPTION
    "Important Awareness Communication"
  ::= { caEventVariables 412 }

newPatchAvailableEvent OBJECT-TYPE
  SYNTAX OCTET STRING (SIZE(0..1000))
  MAX-ACCESS read-only
  STATUS current
  DESCRIPTION
    "A new patch for your software release is available for download"
  ::= { caEventVariables 413 }

knownIssueDetectedDocEvent OBJECT-TYPE
  SYNTAX OCTET STRING (SIZE(0..1000))
  MAX-ACCESS read-only
  STATUS current
  DESCRIPTION
    "Cohesity alert notification."
  ::= { caEventVariables 414 }

knownIssueDetectedHotfixEvent OBJECT-TYPE
  SYNTAX OCTET STRING (SIZE(0..1000))
  MAX-ACCESS read-only
  STATUS current
  DESCRIPTION
    "Cohesity alert notification."
  ::= { caEventVariables 415 }

highUnreachableChunksAlertEvent OBJECT-TYPE
  SYNTAX OCTET STRING (SIZE(0..1000))
  MAX-ACCESS read-only
  STATUS current
  DESCRIPTION
    "Cohesity alert notification."
  ::= { caEventVariables 416 }

remoteStorageRegistrationInvalidEvent OBJECT-TYPE
  SYNTAX OCTET STRING (SIZE(0..1000))
  MAX-ACCESS read-only
  STATUS current
  DESCRIPTION
    "Remote storage registration information is invalid."
  ::= { caEventVariables 418 }

userAccountIsAboutToBeLockedEvent OBJECT-TYPE
  SYNTAX OCTET STRING (SIZE(0..1000))
  MAX-ACCESS read-only
  STATUS current
  DESCRIPTION
    "User account is about to be locked."
  ::= { caEventVariables 419 }

cohesitySnmpTestEvent OBJECT-TYPE
  SYNTAX OCTET STRING (SIZE(0..1000))
  MAX-ACCESS read-only
  STATUS current
  DESCRIPTION
    "Cohesity SNMP Test Notification."
  ::= { caEventVariables 10000 }

-- *****************************************************************
--
-- NOTIFICATION TYPE definition section
--
-- *****************************************************************

diskNotHealthyNotif NOTIFICATION-TYPE
  OBJECTS { diskNotHealthyEvent }
  STATUS current
  DESCRIPTION
    "Disk is not healthy."
  ::= { caNotifsGroup 1 }

nodePingFailedNotif NOTIFICATION-TYPE
  OBJECTS { nodePingFailedEvent }
  STATUS current
  DESCRIPTION
    "Node is not pingable."
  ::= { caNotifsGroup 2 }

markDiskForRemovalNotif NOTIFICATION-TYPE
  OBJECTS { markDiskForRemovalEvent }
  STATUS current
  DESCRIPTION
    "Disk is marked for removal."
  ::= { caNotifsGroup 3 }

upgradeFailedNotif NOTIFICATION-TYPE
  OBJECTS { upgradeFailedEvent }
  STATUS current
  DESCRIPTION
    "Node failed to upgrade."
  ::= { caNotifsGroup 4 }

newDiskFoundNotif NOTIFICATION-TYPE
  OBJECTS { newDiskFoundEvent }
  STATUS current
  DESCRIPTION
    "New disk is found."
  ::= { caNotifsGroup 5 }

diskSpaceLowNotif NOTIFICATION-TYPE
  OBJECTS { diskSpaceLowEvent }
  STATUS current
  DESCRIPTION
    "Disk free space is low."
  ::= { caNotifsGroup 6 }

timeServiceNotif NOTIFICATION-TYPE
  OBJECTS { timeServiceEvent }
  STATUS current
  DESCRIPTION
    "Node can not sync time."
  ::= { caNotifsGroup 7 }

missingDiskNotif NOTIFICATION-TYPE
  OBJECTS { missingDiskEvent }
  STATUS current
  DESCRIPTION
    "One or more disks are missing."
  ::= { caNotifsGroup 8 }

writeLimitNotif NOTIFICATION-TYPE
  OBJECTS { writeLimitEvent }
  STATUS current
  DESCRIPTION
    "SSD is reaching its write limit."
  ::= { caNotifsGroup 9 }

memUncorrectableEccNotif NOTIFICATION-TYPE
  OBJECTS { memUncorrectableEccEvent }
  STATUS current
  DESCRIPTION
    "Memory found uncorrectable ECC."
  ::= { caNotifsGroup 10 }

watchdogTriggeredNotif NOTIFICATION-TYPE
  OBJECTS { watchdogTriggeredEvent }
  STATUS current
  DESCRIPTION
    "IPMI watchdog triggered."
  ::= { caNotifsGroup 12 }

tempOutOfHighRangeNotif NOTIFICATION-TYPE
  OBJECTS { tempOutOfHighRangeEvent }
  STATUS current
  DESCRIPTION
    "Temperature Sensor Out of High Range."
  ::= { caNotifsGroup 13 }

tempOutOfLowRangeNotif NOTIFICATION-TYPE
  OBJECTS { tempOutOfLowRangeEvent }
  STATUS current
  DESCRIPTION
    "Temperature Sensor Out of Low Range."
  ::= { caNotifsGroup 14 }

voltOutOfHighRangeNotif NOTIFICATION-TYPE
  OBJECTS { voltOutOfHighRangeEvent }
  STATUS current
  DESCRIPTION
    "Voltage Sensor Out of High Range."
  ::= { caNotifsGroup 15 }

voltOutOfLowRangeNotif NOTIFICATION-TYPE
  OBJECTS { voltOutOfLowRangeEvent }
  STATUS current
  DESCRIPTION
    "Voltage Sensor Out of Low Range."
  ::= { caNotifsGroup 16 }

driveRemovedNotif NOTIFICATION-TYPE
  OBJECTS { driveRemovedEvent }
  STATUS current
  DESCRIPTION
    "Drive is removed."
  ::= { caNotifsGroup 17 }

drivePresentNotif NOTIFICATION-TYPE
  OBJECTS { drivePresentEvent }
  STATUS current
  DESCRIPTION
    "Drive is present."
  ::= { caNotifsGroup 18 }

driveFaultNotif NOTIFICATION-TYPE
  OBJECTS { driveFaultEvent }
  STATUS current
  DESCRIPTION
    "Drive is faulty."
  ::= { caNotifsGroup 19 }

powerSupplyRemovedNotif NOTIFICATION-TYPE
  OBJECTS { powerSupplyRemovedEvent }
  STATUS current
  DESCRIPTION
    "Power supply is removed."
  ::= { caNotifsGroup 20 }

powerSupplyInsertedNotif NOTIFICATION-TYPE
  OBJECTS { powerSupplyInsertedEvent }
  STATUS current
  DESCRIPTION
    "Power supply is inserted."
  ::= { caNotifsGroup 21 }

linkIsDownNotif NOTIFICATION-TYPE
  OBJECTS { linkIsDownEvent }
  STATUS current
  DESCRIPTION
    "Interface is down."
  ::= { caNotifsGroup 22 }

linkIsUpNotif NOTIFICATION-TYPE
  OBJECTS { linkIsUpEvent }
  STATUS current
  DESCRIPTION
    "Interface is up."
  ::= { caNotifsGroup 23 }

ipmiSelClearedNotif NOTIFICATION-TYPE
  OBJECTS { ipmiSelClearedEvent }
  STATUS current
  DESCRIPTION
    "IPMI SEL log cleared."
  ::= { caNotifsGroup 24 }

nodeRebootedNotif NOTIFICATION-TYPE
  OBJECTS { nodeRebootedEvent }
  STATUS current
  DESCRIPTION
    "Node rebooted."
  ::= { caNotifsGroup 25 }

thermalTripTriggeredNotif NOTIFICATION-TYPE
  OBJECTS { thermalTripTriggeredEvent }
  STATUS current
  DESCRIPTION
    "Thermal Trip Triggered."
  ::= { caNotifsGroup 26 }

powerSupplyAcLostNotif NOTIFICATION-TYPE
  OBJECTS { powerSupplyAcLostEvent }
  STATUS current
  DESCRIPTION
    "Power supply AC lost."
  ::= { caNotifsGroup 27 }

nodeChassisChangedNotif NOTIFICATION-TYPE
  OBJECTS { nodeChassisChangedEvent }
  STATUS current
  DESCRIPTION
    "Chassis is changed."
  ::= { caNotifsGroup 28 }

raidDegradedNotif NOTIFICATION-TYPE
  OBJECTS { raidDegradedEvent }
  STATUS current
  DESCRIPTION
    "RAID is degraded."
  ::= { caNotifsGroup 29 }

diskAddedToClusterNotif NOTIFICATION-TYPE
  OBJECTS { diskAddedToClusterEvent }
  STATUS current
  DESCRIPTION
    "Disk is added to cluster and ready for use."
  ::= { caNotifsGroup 30 }

systemLedAmberNotif NOTIFICATION-TYPE
  OBJECTS { systemLedAmberEvent }
  STATUS current
  DESCRIPTION
    "System amber LED is on."
  ::= { caNotifsGroup 31 }

cpuThrottledNotif NOTIFICATION-TYPE
  OBJECTS { cpuThrottledEvent }
  STATUS current
  DESCRIPTION
    "CPU is throttled."
  ::= { caNotifsGroup 32 }

fanRemovedNotif NOTIFICATION-TYPE
  OBJECTS { fanRemovedEvent }
  STATUS current
  DESCRIPTION
    "Fan is removed."
  ::= { caNotifsGroup 33 }

fanInsertedNotif NOTIFICATION-TYPE
  OBJECTS { fanInsertedEvent }
  STATUS current
  DESCRIPTION
    "Fan is inserted."
  ::= { caNotifsGroup 34 }

fanSpeedOutOfLowRangeNotif NOTIFICATION-TYPE
  OBJECTS { fanSpeedOutOfLowRangeEvent }
  STATUS current
  DESCRIPTION
    "Fan Speed Out of Low Range."
  ::= { caNotifsGroup 35 }

chassisDownNotif NOTIFICATION-TYPE
  OBJECTS { chassisDownEvent }
  STATUS current
  DESCRIPTION
    "All nodes in the chassis are unreachable."
  ::= { caNotifsGroup 36 }

ipmiUnreachableNotif NOTIFICATION-TYPE
  OBJECTS { ipmiUnreachableEvent }
  STATUS current
  DESCRIPTION
    "IPMI unreachable."
  ::= { caNotifsGroup 37 }

ipmiNetworkConfigFailedNotif NOTIFICATION-TYPE
  OBJECTS { ipmiNetworkConfigFailedEvent }
  STATUS current
  DESCRIPTION
    "IPMI network configured failed."
  ::= { caNotifsGroup 38 }

ipmiUserUpdateFailedNotif NOTIFICATION-TYPE
  OBJECTS { ipmiUserUpdateFailedEvent }
  STATUS current
  DESCRIPTION
    "IPMI user update failed."
  ::= { caNotifsGroup 39 }

ipmiConfigAbsentNotif NOTIFICATION-TYPE
  OBJECTS { ipmiConfigAbsentEvent }
  STATUS current
  DESCRIPTION
    "IPMI config absent in cluster."
  ::= { caNotifsGroup 40 }

ipmiEventNotif NOTIFICATION-TYPE
  OBJECTS { ipmiEventEvent }
  STATUS current
  DESCRIPTION
    "IPMI enent notification"
  ::= { caNotifsGroup 41 }

storageDomainQuotaNotif NOTIFICATION-TYPE
  OBJECTS { storageDomainQuotaEvent }
  STATUS current
  DESCRIPTION
    "Storage domain usage exceeded quota alert limit"
  ::= { caNotifsGroup 42 }

yodaAgentUnhealthyNotif NOTIFICATION-TYPE
  OBJECTS { yodaAgentUnhealthyEvent }
  STATUS current
  DESCRIPTION
    "Yoda agent health check failed."
  ::= { caNotifsGroup 43 }

searchIndexManualMigrationNeededNotif NOTIFICATION-TYPE
  OBJECTS { searchIndexManualMigrationNeededEvent }
  STATUS current
  DESCRIPTION
    "Manual Migration to Librarian is required."
  ::= { caNotifsGroup 44 }

searchIndexMigrationFinishedNotif NOTIFICATION-TYPE
  OBJECTS { searchIndexMigrationFinishedEvent }
  STATUS current
  DESCRIPTION
    "Search index migration to Librarian finished."
  ::= { caNotifsGroup 45 }

searchIndexMigrationTriggeredNotif NOTIFICATION-TYPE
  OBJECTS { searchIndexMigrationTriggeredEvent }
  STATUS current
  DESCRIPTION
    "Search index migration to Librarian triggered."
  ::= { caNotifsGroup 46 }

searchIndexMigrationBacklogNotif NOTIFICATION-TYPE
  OBJECTS { searchIndexMigrationBacklogEvent }
  STATUS current
  DESCRIPTION
    "Search index migration to Librarian is taking longer than expected."
  ::= { caNotifsGroup 47 }

vMOptimizedXFSVolumeIndexingSkippedNotif NOTIFICATION-TYPE
  OBJECTS { vMOptimizedXFSVolumeIndexingSkippedEvent }
  STATUS current
  DESCRIPTION
    "Optimized XFS indexing path skipped some server volumes."
  ::= { caNotifsGroup 48 }

vMOptimizedNTFSVolumeIndexingSkippedNotif NOTIFICATION-TYPE
  OBJECTS { vMOptimizedNTFSVolumeIndexingSkippedEvent }
  STATUS current
  DESCRIPTION
    "Optimized NTFS indexing path skipped some server volumes."
  ::= { caNotifsGroup 49 }

aVThreatFoundNotif NOTIFICATION-TYPE
  OBJECTS { aVThreatFoundEvent }
  STATUS current
  DESCRIPTION
    "Virus found by antivirus provider"
  ::= { caNotifsGroup 50 }

corruptFileSystemNotIndexedNotif NOTIFICATION-TYPE
  OBJECTS { corruptFileSystemNotIndexedEvent }
  STATUS current
  DESCRIPTION
    "Indexing of object with corrupt filesystem is skipped."
  ::= { caNotifsGroup 51 }

indexingPausedNotif NOTIFICATION-TYPE
  OBJECTS { indexingPausedEvent }
  STATUS current
  DESCRIPTION
    "Indexing of object contents paused."
  ::= { caNotifsGroup 52 }

viewQuotaNotif NOTIFICATION-TYPE
  OBJECTS { viewQuotaEvent }
  STATUS current
  DESCRIPTION
    "View usage exceeded quota alert limit"
  ::= { caNotifsGroup 53 }

usersExceededQuotaNotif NOTIFICATION-TYPE
  OBJECTS { usersExceededQuotaEvent }
  STATUS current
  DESCRIPTION
    "Some users exceeded their logical alert limit"
  ::= { caNotifsGroup 54 }

notEnoughNodesNotif NOTIFICATION-TYPE
  OBJECTS { notEnoughNodesEvent }
  STATUS current
  DESCRIPTION
    "More nodes need to be added"
  ::= { caNotifsGroup 55 }

aVServerLicenseErrorNotif NOTIFICATION-TYPE
  OBJECTS { aVServerLicenseErrorEvent }
  STATUS current
  DESCRIPTION
    "Antivirus provider license is expired"
  ::= { caNotifsGroup 56 }

internalSchedulingWarningNotif NOTIFICATION-TYPE
  OBJECTS { internalSchedulingWarningEvent }
  STATUS current
  DESCRIPTION
    "Internal scheduling issue"
  ::= { caNotifsGroup 57 }

cloudTierWarningNotif NOTIFICATION-TYPE
  OBJECTS { cloudTierWarningEvent }
  STATUS current
  DESCRIPTION
    "Cloud tier warning"
  ::= { caNotifsGroup 58 }

switchCongestionNotif NOTIFICATION-TYPE
  OBJECTS { switchCongestionEvent }
  STATUS current
  DESCRIPTION
    "Ethernet traffic is experiencing congestion on interface  on node  with ip "
  ::= { caNotifsGroup 59 }

nodeVirtualizationSupportDisabledNotif NOTIFICATION-TYPE
  OBJECTS { nodeVirtualizationSupportDisabledEvent }
  STATUS current
  DESCRIPTION
    "Virtualization support is disabled on node  with ip "
  ::= { caNotifsGroup 60 }

sshTimeoutChangedNotif NOTIFICATION-TYPE
  OBJECTS { sshTimeoutChangedEvent }
  STATUS current
  DESCRIPTION
    "Ssh timeout configuration changed on node  with ip "
  ::= { caNotifsGroup 61 }

bondUnhealthyNotif NOTIFICATION-TYPE
  OBJECTS { bondUnhealthyEvent }
  STATUS current
  DESCRIPTION
    "Bond interface is unhealthy on node"
  ::= { caNotifsGroup 62 }

bondSlavesSpeedInconsistentNotif NOTIFICATION-TYPE
  OBJECTS { bondSlavesSpeedInconsistentEvent }
  STATUS current
  DESCRIPTION
    "Bond slaves' speed are inconsistent on interface  on node  with ip "
  ::= { caNotifsGroup 63 }

unexpectedInterfaceIpSettingNotif NOTIFICATION-TYPE
  OBJECTS { unexpectedInterfaceIpSettingEvent }
  STATUS current
  DESCRIPTION
    "Static IP on some interfaces is not configured in interface group"
  ::= { caNotifsGroup 64 }

scriptRunErrorNotif NOTIFICATION-TYPE
  OBJECTS { scriptRunErrorEvent }
  STATUS current
  DESCRIPTION
    "Health check script  has errors"
  ::= { caNotifsGroup 65 }

diskIsBadNotif NOTIFICATION-TYPE
  OBJECTS { diskIsBadEvent }
  STATUS current
  DESCRIPTION
    "Disk is bad"
  ::= { caNotifsGroup 66 }

adDomainControllersNotReachableNotif NOTIFICATION-TYPE
  OBJECTS { adDomainControllersNotReachableEvent }
  STATUS current
  DESCRIPTION
    "Active directory domain controller is not reachable"
  ::= { caNotifsGroup 67 }

upgradeStuckNotif NOTIFICATION-TYPE
  OBJECTS { upgradeStuckEvent }
  STATUS current
  DESCRIPTION
    "Upgrade is taking longer than usual"
  ::= { caNotifsGroup 68 }

productModelIncompatibleNotif NOTIFICATION-TYPE
  OBJECTS { productModelIncompatibleEvent }
  STATUS current
  DESCRIPTION
    "Product models are not compatible on the node  with ip "
  ::= { caNotifsGroup 69 }

directoriesExceededQuotaNotif NOTIFICATION-TYPE
  OBJECTS { directoriesExceededQuotaEvent }
  STATUS current
  DESCRIPTION
    "Some directories exceeded their logical alert limit"
  ::= { caNotifsGroup 70 }

algorithmBacklogAlertNotif NOTIFICATION-TYPE
  OBJECTS { algorithmBacklogAlertEvent }
  STATUS current
  DESCRIPTION
    "A background system algorithm is backlogged."
  ::= { caNotifsGroup 71 }

clearStaleMountPointsTimeoutNotif NOTIFICATION-TYPE
  OBJECTS { clearStaleMountPointsTimeoutEvent }
  STATUS current
  DESCRIPTION
    "Timeout while trying to clear stale mount points."
  ::= { caNotifsGroup 72 }

addNodeFailedNotif NOTIFICATION-TYPE
  OBJECTS { addNodeFailedEvent }
  STATUS current
  DESCRIPTION
    "Node failed to join the cluster"
  ::= { caNotifsGroup 73 }

directoryExceededQuotaAlertLimitNotif NOTIFICATION-TYPE
  OBJECTS { directoryExceededQuotaAlertLimitEvent }
  STATUS current
  DESCRIPTION
    "Directory exceeded the logical alert limit"
  ::= { caNotifsGroup 74 }

clusterBringupErrorNotif NOTIFICATION-TYPE
  OBJECTS { clusterBringupErrorEvent }
  STATUS current
  DESCRIPTION
    "Error found during cluster bring up on cluster"
  ::= { caNotifsGroup 75 }

chunkFileBadStateNotif NOTIFICATION-TYPE
  OBJECTS { chunkFileBadStateEvent }
  STATUS current
  DESCRIPTION
    "Chunk file  in Storage domain  is in bad state for long time"
  ::= { caNotifsGroup 76 }

tablesLargerThanExpectedNotif NOTIFICATION-TYPE
  OBJECTS { tablesLargerThanExpectedEvent }
  STATUS current
  DESCRIPTION
    "Table size, for table is larger than an expected fraction of the disk's metadata capacity"
  ::= { caNotifsGroup 77 }

keyRotationPolicyChangedNotif NOTIFICATION-TYPE
  OBJECTS { keyRotationPolicyChangedEvent }
  STATUS current
  DESCRIPTION
    "Key rotation policy has been changed."
  ::= { caNotifsGroup 78 }

potentialClusterErrorNotif NOTIFICATION-TYPE
  OBJECTS { potentialClusterErrorEvent }
  STATUS current
  DESCRIPTION
    "Cluster  might have an internal error that requires action by Cohesity Support"
  ::= { caNotifsGroup 79 }

clusterGatewayUnReachableNotif NOTIFICATION-TYPE
  OBJECTS { clusterGatewayUnReachableEvent }
  STATUS current
  DESCRIPTION
    "Cluster gateway is not reachable."
  ::= { caNotifsGroup 80 }

dnsServerUnReachableNotif NOTIFICATION-TYPE
  OBJECTS { dnsServerUnReachableEvent }
  STATUS current
  DESCRIPTION
    "DNS server is not reachable."
  ::= { caNotifsGroup 81 }

verifyVlanHostNameNotif NOTIFICATION-TYPE
  OBJECTS { verifyVlanHostNameEvent }
  STATUS current
  DESCRIPTION
    "Error while verifying hostname entry in DNS server for the interface group "
  ::= { caNotifsGroup 82 }

lowFaultTolerantStorageDomainNotif NOTIFICATION-TYPE
  OBJECTS { lowFaultTolerantStorageDomainEvent }
  STATUS current
  DESCRIPTION
    "Low fault tolerant storage domain found for cluster"
  ::= { caNotifsGroup 83 }

securityPolicyDenialNotif NOTIFICATION-TYPE
  OBJECTS { securityPolicyDenialEvent }
  STATUS current
  DESCRIPTION
    "Security policy denial found on node  with ip "
  ::= { caNotifsGroup 84 }

bondModeAutoMigratedNotif NOTIFICATION-TYPE
  OBJECTS { bondModeAutoMigratedEvent }
  STATUS current
  DESCRIPTION
    "Node  with ip  bond mode has been migrated"
  ::= { caNotifsGroup 85 }

nisDomainNotReachableNotif NOTIFICATION-TYPE
  OBJECTS { nisDomainNotReachableEvent }
  STATUS current
  DESCRIPTION
    "NIS domain  is not reachable."
  ::= { caNotifsGroup 86 }

nodeRemovedNotif NOTIFICATION-TYPE
  OBJECTS { nodeRemovedEvent }
  STATUS current
  DESCRIPTION
    "Node was disconnected or removed"
  ::= { caNotifsGroup 87 }

nodeInsertedNotif NOTIFICATION-TYPE
  OBJECTS { nodeInsertedEvent }
  STATUS current
  DESCRIPTION
    "Node was inserted"
  ::= { caNotifsGroup 88 }

inconsistentStaticRoutesNotif NOTIFICATION-TYPE
  OBJECTS { inconsistentStaticRoutesEvent }
  STATUS current
  DESCRIPTION
    "One or more inconsistent static routes with cluster config on node  with ip "
  ::= { caNotifsGroup 89 }

chunkFileInconsistencyNotif NOTIFICATION-TYPE
  OBJECTS { chunkFileInconsistencyEvent }
  STATUS current
  DESCRIPTION
    "Cluster might have an internal error that requires action by Cohesity Support"
  ::= { caNotifsGroup 90 }

accessToExternalTargetFailedNotif NOTIFICATION-TYPE
  OBJECTS { accessToExternalTargetFailedEvent }
  STATUS current
  DESCRIPTION
    "Access to external target  failed"
  ::= { caNotifsGroup 91 }

remoteReplicationBackupUserQuotaSkippedNotif NOTIFICATION-TYPE
  OBJECTS { remoteReplicationBackupUserQuotaSkippedEvent }
  STATUS current
  DESCRIPTION
    "Replication to remote cluster  for job  skipped user quota data backup"
  ::= { caNotifsGroup 92 }

remoteReplicationRestoreUserQuotaSkippedNotif NOTIFICATION-TYPE
  OBJECTS { remoteReplicationRestoreUserQuotaSkippedEvent }
  STATUS current
  DESCRIPTION
    "Replication to this cluster skipped user quota data restore"
  ::= { caNotifsGroup 93 }

remoteReplicationFileSkippedNotif NOTIFICATION-TYPE
  OBJECTS { remoteReplicationFileSkippedEvent }
  STATUS current
  DESCRIPTION
    "Replication to remote cluster  for job  skipped unsupported file"
  ::= { caNotifsGroup 94 }

chunkFileReplicaBadStateNotif NOTIFICATION-TYPE
  OBJECTS { chunkFileReplicaBadStateEvent }
  STATUS current
  DESCRIPTION
    "Cluster might have an internal error that requires action by Cohesity Support"
  ::= { caNotifsGroup 95 }

remoteReplicationSetupIncompatibleNotif NOTIFICATION-TYPE
  OBJECTS { remoteReplicationSetupIncompatibleEvent }
  STATUS current
  DESCRIPTION
    "Replication setup is incompatible"
  ::= { caNotifsGroup 96 }

taskProgressHungNotif NOTIFICATION-TYPE
  OBJECTS { taskProgressHungEvent }
  STATUS current
  DESCRIPTION
    "Root task  has some hung sub tasks"
  ::= { caNotifsGroup 97 }

missingDiskFilesNotif NOTIFICATION-TYPE
  OBJECTS { missingDiskFilesEvent }
  STATUS current
  DESCRIPTION
    "One or more disk files missing for indexing."
  ::= { caNotifsGroup 98 }

nodePoweredOffNotif NOTIFICATION-TYPE
  OBJECTS { nodePoweredOffEvent }
  STATUS current
  DESCRIPTION
    "Node was powered off"
  ::= { caNotifsGroup 99 }

metadataInconsistencyAlertNotif NOTIFICATION-TYPE
  OBJECTS { metadataInconsistencyAlertEvent }
  STATUS current
  DESCRIPTION
    "Internal error detected for cluster."
  ::= { caNotifsGroup 100 }

diskMarkedOfflineNotif NOTIFICATION-TYPE
  OBJECTS { diskMarkedOfflineEvent }
  STATUS current
  DESCRIPTION
    "Disk is marked offline."
  ::= { caNotifsGroup 101 }

activeDirectoryNotReachableNotif NOTIFICATION-TYPE
  OBJECTS { activeDirectoryNotReachableEvent }
  STATUS current
  DESCRIPTION
    "Active directory is not reachable."
  ::= { caNotifsGroup 102 }

kernelPanicNotif NOTIFICATION-TYPE
  OBJECTS { kernelPanicEvent }
  STATUS current
  DESCRIPTION
    "Node crashed from a kernel panic."
  ::= { caNotifsGroup 103 }

clusterSpaceUsageHighNotif NOTIFICATION-TYPE
  OBJECTS { clusterSpaceUsageHighEvent }
  STATUS current
  DESCRIPTION
    "Cluster space usage is high."
  ::= { caNotifsGroup 104 }

storageDomainSpaceUsageHighNotif NOTIFICATION-TYPE
  OBJECTS { storageDomainSpaceUsageHighEvent }
  STATUS current
  DESCRIPTION
    "Storage domain space usage is high."
  ::= { caNotifsGroup 105 }

nodeFailureIsNotToleratedNotif NOTIFICATION-TYPE
  OBJECTS { nodeFailureIsNotToleratedEvent }
  STATUS current
  DESCRIPTION
    "Cluster is not able to tolerate node failure."
  ::= { caNotifsGroup 106 }

searchClusterHealthNotif NOTIFICATION-TYPE
  OBJECTS { searchClusterHealthEvent }
  STATUS current
  DESCRIPTION
    "Search cluster is not healthy."
  ::= { caNotifsGroup 107 }

protectionGroupFailedNotif NOTIFICATION-TYPE
  OBJECTS { protectionGroupFailedEvent }
  STATUS current
  DESCRIPTION
    "Backup run of job failed."
  ::= { caNotifsGroup 108 }

protectedObjectFailedNotif NOTIFICATION-TYPE
  OBJECTS { protectedObjectFailedEvent }
  STATUS current
  DESCRIPTION
    "Backup run of object failed."
  ::= { caNotifsGroup 109 }

metadataServerUnreachableNotif NOTIFICATION-TYPE
  OBJECTS { metadataServerUnreachableEvent }
  STATUS current
  DESCRIPTION
    "Metadata server unreachable for long time."
  ::= { caNotifsGroup 110 }

metadataUnavailableNotif NOTIFICATION-TYPE
  OBJECTS { metadataUnavailableEvent }
  STATUS current
  DESCRIPTION
    "Metadata is unavailable due to multiple failures."
  ::= { caNotifsGroup 111 }

metadataShuffleNotProgressingNotif NOTIFICATION-TYPE
  OBJECTS { metadataShuffleNotProgressingEvent }
  STATUS current
  DESCRIPTION
    "Metadata shuffle not progressing due to load constraint."
  ::= { caNotifsGroup 112 }

searchIndexSizeExceedsThresholdNotif NOTIFICATION-TYPE
  OBJECTS { searchIndexSizeExceedsThresholdEvent }
  STATUS current
  DESCRIPTION
    "Search index size is approaching threshold."
  ::= { caNotifsGroup 113 }

searchIndexShuffleNotProgressingNotif NOTIFICATION-TYPE
  OBJECTS { searchIndexShuffleNotProgressingEvent }
  STATUS current
  DESCRIPTION
    "Data shuffle for search index is not progressing."
  ::= { caNotifsGroup 114 }

metadataCannotTolerateAnymoreFailuresNotif NOTIFICATION-TYPE
  OBJECTS { metadataCannotTolerateAnymoreFailuresEvent }
  STATUS current
  DESCRIPTION
    "Metadata cannot tolerate anymore failures."
  ::= { caNotifsGroup 115 }

metadataCannotAchieveConfiguredFaultToleranceFactorNotif NOTIFICATION-TYPE
  OBJECTS { metadataCannotAchieveConfiguredFaultToleranceFactorEvent }
  STATUS current
  DESCRIPTION
    "Metadata cannot achieve configured fault tolerance factor."
  ::= { caNotifsGroup 116 }

searchIndexUnavailableNotif NOTIFICATION-TYPE
  OBJECTS { searchIndexUnavailableEvent }
  STATUS current
  DESCRIPTION
    "Search index cannot achieve configured fault tolerance factor."
  ::= { caNotifsGroup 117 }

metadataCanRunOutOfSpaceUponFailureNotif NOTIFICATION-TYPE
  OBJECTS { metadataCanRunOutOfSpaceUponFailureEvent }
  STATUS current
  DESCRIPTION
    "Metadata can run out of space upon failure."
  ::= { caNotifsGroup 118 }

diskAddedToBlacklistNotif NOTIFICATION-TYPE
  OBJECTS { diskAddedToBlacklistEvent }
  STATUS current
  DESCRIPTION
    "Disk is added to blacklist."
  ::= { caNotifsGroup 119 }

diskSlotAvailableNotif NOTIFICATION-TYPE
  OBJECTS { diskSlotAvailableEvent }
  STATUS current
  DESCRIPTION
    "One or more unused disk slots are available."
  ::= { caNotifsGroup 120 }

protectionGroupSlaViolatedNotif NOTIFICATION-TYPE
  OBJECTS { protectionGroupSlaViolatedEvent }
  STATUS current
  DESCRIPTION
    "SLA of backup run of job violated."
  ::= { caNotifsGroup 121 }

protectionGroupcanceledBlackoutWindowNotif NOTIFICATION-TYPE
  OBJECTS { protectionGroupcanceledBlackoutWindowEvent }
  STATUS current
  DESCRIPTION
    "Backup run of job was cancelled due to hitting blackout window."
  ::= { caNotifsGroup 122 }

policyFieldsDeprecatedNotif NOTIFICATION-TYPE
  OBJECTS { policyFieldsDeprecatedEvent }
  STATUS current
  DESCRIPTION
    "Policy settings of a policy have been deprecated."
  ::= { caNotifsGroup 123 }

protectedObjectCancelledBlackoutWindowNotif NOTIFICATION-TYPE
  OBJECTS { protectedObjectCancelledBlackoutWindowEvent }
  STATUS current
  DESCRIPTION
    "Backup of object that is part of job run was cancelled due to blackout window."
  ::= { caNotifsGroup 124 }

protectionGroupArchivalBacklogNotif NOTIFICATION-TYPE
  OBJECTS { protectionGroupArchivalBacklogEvent }
  STATUS current
  DESCRIPTION
    "Backup job has archival tasks with high queue wait times."
  ::= { caNotifsGroup 125 }

archiveJobFailedNotif NOTIFICATION-TYPE
  OBJECTS { archiveJobFailedEvent }
  STATUS current
  DESCRIPTION
    "Archive task has failed."
  ::= { caNotifsGroup 126 }

archiveJobStuckNotif NOTIFICATION-TYPE
  OBJECTS { archiveJobStuckEvent }
  STATUS current
  DESCRIPTION
    "Archive task is not making progress."
  ::= { caNotifsGroup 127 }

restoreJobFailedNotif NOTIFICATION-TYPE
  OBJECTS { restoreJobFailedEvent }
  STATUS current
  DESCRIPTION
    "Restore task has progress."
  ::= { caNotifsGroup 128 }

restoreJobStuckNotif NOTIFICATION-TYPE
  OBJECTS { restoreJobStuckEvent }
  STATUS current
  DESCRIPTION
    "Restore task is not making progress."
  ::= { caNotifsGroup 129 }

protectedObjectSlaViolatedNotif NOTIFICATION-TYPE
  OBJECTS { protectedObjectSlaViolatedEvent }
  STATUS current
  DESCRIPTION
    "Backup of object violated SLA in a backup run."
  ::= { caNotifsGroup 130 }

protectionGroupReplicationBacklogNotif NOTIFICATION-TYPE
  OBJECTS { protectionGroupReplicationBacklogEvent }
  STATUS current
  DESCRIPTION
    "Backup job has replication tasks with high queue wait times."
  ::= { caNotifsGroup 131 }

missingVMBackupNotif NOTIFICATION-TYPE
  OBJECTS { missingVMBackupEvent }
  STATUS current
  DESCRIPTION
    "Missing VM Backup."
  ::= { caNotifsGroup 132 }

vMCrackingSkippedNotif NOTIFICATION-TYPE
  OBJECTS { vMCrackingSkippedEvent }
  STATUS current
  DESCRIPTION
    "VM contents not indexed."
  ::= { caNotifsGroup 133 }

vMWareMountFailureNotif NOTIFICATION-TYPE
  OBJECTS { vMWareMountFailureEvent }
  STATUS current
  DESCRIPTION
    "Too many VMWare mount failures."
  ::= { caNotifsGroup 134 }

vMVolumeIndexingSkippedNotif NOTIFICATION-TYPE
  OBJECTS { vMVolumeIndexingSkippedEvent }
  STATUS current
  DESCRIPTION
    "VM one or more volume indexing skipped."
  ::= { caNotifsGroup 135 }

remoteReplicationTaskStuckNotif NOTIFICATION-TYPE
  OBJECTS { remoteReplicationTaskStuckEvent }
  STATUS current
  DESCRIPTION
    "Replication to remote cluster is stuck for a job."
  ::= { caNotifsGroup 136 }

remoteReplicationTaskFailedNotif NOTIFICATION-TYPE
  OBJECTS { remoteReplicationTaskFailedEvent }
  STATUS current
  DESCRIPTION
    "Replication to remote cluster has failed for a job."
  ::= { caNotifsGroup 137 }

frequentProcessRestartsNotif NOTIFICATION-TYPE
  OBJECTS { frequentProcessRestartsEvent }
  STATUS current
  DESCRIPTION
    "Process is being restarted frequently."
  ::= { caNotifsGroup 138 }

protectionGroupProgressingSlowlyNotif NOTIFICATION-TYPE
  OBJECTS { protectionGroupProgressingSlowlyEvent }
  STATUS current
  DESCRIPTION
    "Protection group is progressing slowly."
  ::= { caNotifsGroup 139 }

mtuUnexpectedNotif NOTIFICATION-TYPE
  OBJECTS { mtuUnexpectedEvent }
  STATUS current
  DESCRIPTION
    "MTU does not match expected configuration on the node  with ip "
  ::= { caNotifsGroup 140 }

gatewayUnexpectedNotif NOTIFICATION-TYPE
  OBJECTS { gatewayUnexpectedEvent }
  STATUS current
  DESCRIPTION
    "Gateway does not match expected configuration on the node  with ip "
  ::= { caNotifsGroup 141 }

linkStatsIsNotNormalNotif NOTIFICATION-TYPE
  OBJECTS { linkStatsIsNotNormalEvent }
  STATUS current
  DESCRIPTION
    "Errors detected in the network Physical layer"
  ::= { caNotifsGroup 142 }

upgradeSucceededNotif NOTIFICATION-TYPE
  OBJECTS { upgradeSucceededEvent }
  STATUS current
  DESCRIPTION
    "Upgrade succeeded on the node to "
  ::= { caNotifsGroup 143 }

upgradeStartedNotif NOTIFICATION-TYPE
  OBJECTS { upgradeStartedEvent }
  STATUS current
  DESCRIPTION
    "Upgrade started on the node"
  ::= { caNotifsGroup 144 }

bondingModeUnexpectedNotif NOTIFICATION-TYPE
  OBJECTS { bondingModeUnexpectedEvent }
  STATUS current
  DESCRIPTION
    "Bonding mode does not match expected configuration on the node"
  ::= { caNotifsGroup 145 }

vLANUnexpectedNotif NOTIFICATION-TYPE
  OBJECTS { vLANUnexpectedEvent }
  STATUS current
  DESCRIPTION
    "Unexpected VLAN found on node  with ip ."
  ::= { caNotifsGroup 146 }

kIntegralVolumeReachingMaxCapacityNotif NOTIFICATION-TYPE
  OBJECTS { kIntegralVolumeReachingMaxCapacityEvent }
  STATUS current
  DESCRIPTION
    "Current integral volume on QStar host reaching its max capacity limit."
  ::= { caNotifsGroup 147 }

mediaErrorDuringRestoreNotif NOTIFICATION-TYPE
  OBJECTS { mediaErrorDuringRestoreEvent }
  STATUS current
  DESCRIPTION
    "Restore task is waiting to correct the error"
  ::= { caNotifsGroup 148 }

mediaErrorDuringArchivalNotif NOTIFICATION-TYPE
  OBJECTS { mediaErrorDuringArchivalEvent }
  STATUS current
  DESCRIPTION
    "Archival job is waiting to correct the error"
  ::= { caNotifsGroup 149 }

diskWithTooManyDeltaRecordsNotif NOTIFICATION-TYPE
  OBJECTS { diskWithTooManyDeltaRecordsEvent }
  STATUS current
  DESCRIPTION
    "Disk  has too many internal metadata records"
  ::= { caNotifsGroup 150 }

unresponsiveChildDeathNotif NOTIFICATION-TYPE
  OBJECTS { unresponsiveChildDeathEvent }
  STATUS current
  DESCRIPTION
    "Process  is unresponsive"
  ::= { caNotifsGroup 151 }

encryptionKeyRotatedNotif NOTIFICATION-TYPE
  OBJECTS { encryptionKeyRotatedEvent }
  STATUS current
  DESCRIPTION
    "Encryption key has been rotated."
  ::= { caNotifsGroup 152 }

encryptionKeyCreatedNotif NOTIFICATION-TYPE
  OBJECTS { encryptionKeyCreatedEvent }
  STATUS current
  DESCRIPTION
    "A new encryption key has been created."
  ::= { caNotifsGroup 153 }

newUpgradePackagesAvailableNotif NOTIFICATION-TYPE
  OBJECTS { newUpgradePackagesAvailableEvent }
  STATUS current
  DESCRIPTION
    "New upgrade packages available on the node  with IP  to "
  ::= { caNotifsGroup 154 }

invalidStateNotif NOTIFICATION-TYPE
  OBJECTS { invalidStateEvent }
  STATUS current
  DESCRIPTION
    "Node  with ip  entered an invalid state"
  ::= { caNotifsGroup 155 }

metadataSizeExceedsThresholdNotif NOTIFICATION-TYPE
  OBJECTS { metadataSizeExceedsThresholdEvent }
  STATUS current
  DESCRIPTION
    "Metadata size on disk exceeding threshold"
  ::= { caNotifsGroup 156 }

keystoneNotReachableNotif NOTIFICATION-TYPE
  OBJECTS { keystoneNotReachableEvent }
  STATUS current
  DESCRIPTION
    "Keystone  is not reachable."
  ::= { caNotifsGroup 157 }

dataResilienceAtRiskNotif NOTIFICATION-TYPE
  OBJECTS { dataResilienceAtRiskEvent }
  STATUS current
  DESCRIPTION
    "Data resilience at risk"
  ::= { caNotifsGroup 158 }

diskAwaitHighNotif NOTIFICATION-TYPE
  OBJECTS { diskAwaitHighEvent }
  STATUS current
  DESCRIPTION
    "Await time for disk ID is too high"
  ::= { caNotifsGroup 159 }

raidInactiveNotif NOTIFICATION-TYPE
  OBJECTS { raidInactiveEvent }
  STATUS current
  DESCRIPTION
    "Node  with ip  has inactive RAID disks "
  ::= { caNotifsGroup 160 }

removeNodeSuccessNotif NOTIFICATION-TYPE
  OBJECTS { removeNodeSuccessEvent }
  STATUS current
  DESCRIPTION
    "Removal of node is successful"
  ::= { caNotifsGroup 161 }

routesMigrationOnBondFailedNotif NOTIFICATION-TYPE
  OBJECTS { routesMigrationOnBondFailedEvent }
  STATUS current
  DESCRIPTION
    "Node  with ip  routes migration to bond failed"
  ::= { caNotifsGroup 162 }

serviceDownNotif NOTIFICATION-TYPE
  OBJECTS { serviceDownEvent }
  STATUS current
  DESCRIPTION
    " service on the node  with ip  is down"
  ::= { caNotifsGroup 163 }

configureVipFailedNotif NOTIFICATION-TYPE
  OBJECTS { configureVipFailedEvent }
  STATUS current
  DESCRIPTION
    "Failed to configure VIP"
  ::= { caNotifsGroup 164 }

ipMigrationOnBondFailedNotif NOTIFICATION-TYPE
  OBJECTS { ipMigrationOnBondFailedEvent }
  STATUS current
  DESCRIPTION
    "Node  with ip  IP migration to bond failed"
  ::= { caNotifsGroup 165 }

firewallErrorNotif NOTIFICATION-TYPE
  OBJECTS { firewallErrorEvent }
  STATUS current
  DESCRIPTION
    "Cluster firewall on node has errors"
  ::= { caNotifsGroup 166 }

usbDiskFoundNotif NOTIFICATION-TYPE
  OBJECTS { usbDiskFoundEvent }
  STATUS current
  DESCRIPTION
    "Usb disk  detected on the node  with ip "
  ::= { caNotifsGroup 167 }

bootDiskHealthNotif NOTIFICATION-TYPE
  OBJECTS { bootDiskHealthEvent }
  STATUS current
  DESCRIPTION
    "Boot disk maybe unhealthy on the node  with ip "
  ::= { caNotifsGroup 168 }

etcHostsFileErrorNotif NOTIFICATION-TYPE
  OBJECTS { etcHostsFileErrorEvent }
  STATUS current
  DESCRIPTION
    "Etc hosts file on node  with ip  has errors"
  ::= { caNotifsGroup 169 }

smallMemorySizeNotif NOTIFICATION-TYPE
  OBJECTS { smallMemorySizeEvent }
  STATUS current
  DESCRIPTION
    "Node  with ip  does not meet minimum memory size requirements"
  ::= { caNotifsGroup 170 }

userExceededQuotaAlertLimitNotif NOTIFICATION-TYPE
  OBJECTS { userExceededQuotaAlertLimitEvent }
  STATUS current
  DESCRIPTION
    "User exceeded the logical alert limit"
  ::= { caNotifsGroup 171 }

addNodeSuccessNotif NOTIFICATION-TYPE
  OBJECTS { addNodeSuccessEvent }
  STATUS current
  DESCRIPTION
    "Node has joined the cluster"
  ::= { caNotifsGroup 172 }

forcefulRemoveNodeWarningNotif NOTIFICATION-TYPE
  OBJECTS { forcefulRemoveNodeWarningEvent }
  STATUS current
  DESCRIPTION
    "Node is being removed from the cluster forcefully"
  ::= { caNotifsGroup 173 }

aVServerConnectionFailedNotif NOTIFICATION-TYPE
  OBJECTS { aVServerConnectionFailedEvent }
  STATUS current
  DESCRIPTION
    "Antivirus provider is not reachable"
  ::= { caNotifsGroup 174 }

adPreferredDomainControllerNotReachableNotif NOTIFICATION-TYPE
  OBJECTS { adPreferredDomainControllerNotReachableEvent }
  STATUS current
  DESCRIPTION
    "Preferred domain controller is not reachable"
  ::= { caNotifsGroup 175 }

blobJournalInconsistencyNotif NOTIFICATION-TYPE
  OBJECTS { blobJournalInconsistencyEvent }
  STATUS current
  DESCRIPTION
    "Cluster might have an internal error that requires action by Cohesity Support"
  ::= { caNotifsGroup 176 }

viewLatencyHighNotif NOTIFICATION-TYPE
  OBJECTS { viewLatencyHighEvent }
  STATUS current
  DESCRIPTION
    "View latency exceeds threshold"
  ::= { caNotifsGroup 177 }

potentialMinorClusterErrorNotif NOTIFICATION-TYPE
  OBJECTS { potentialMinorClusterErrorEvent }
  STATUS current
  DESCRIPTION
    "Cluster  might have an internal error that requires action by Cohesity Support"
  ::= { caNotifsGroup 178 }

iceboxDedupCacheFullNotif NOTIFICATION-TYPE
  OBJECTS { iceboxDedupCacheFullEvent }
  STATUS current
  DESCRIPTION
    "Icebox dedup cache is full"
  ::= { caNotifsGroup 179 }

clusterServiceGflagsFoundNotif NOTIFICATION-TYPE
  OBJECTS { clusterServiceGflagsFoundEvent }
  STATUS current
  DESCRIPTION
    "Found cluster service gflags."
  ::= { caNotifsGroup 180 }

virtualApplianceResourcesUnexpectedNotif NOTIFICATION-TYPE
  OBJECTS { virtualApplianceResourcesUnexpectedEvent }
  STATUS current
  DESCRIPTION
    "The resources for the virtual appliance on node is not matching Cohesity recommendations"
  ::= { caNotifsGroup 181 }

clusterPartitionCreateFailedNotif NOTIFICATION-TYPE
  OBJECTS { clusterPartitionCreateFailedEvent }
  STATUS current
  DESCRIPTION
    "Could not create cluster partition."
  ::= { caNotifsGroup 182 }

proxyServerUnreachableNotif NOTIFICATION-TYPE
  OBJECTS { proxyServerUnreachableEvent }
  STATUS current
  DESCRIPTION
    "Proxy server is unreachable on the node  with ip "
  ::= { caNotifsGroup 183 }

serviceVersionsMismatchedNotif NOTIFICATION-TYPE
  OBJECTS { serviceVersionsMismatchedEvent }
  STATUS current
  DESCRIPTION
    "Cohesity nodes are running different versions of software in the same cluster"
  ::= { caNotifsGroup 184 }

firmwareIncompatibleNotif NOTIFICATION-TYPE
  OBJECTS { firmwareIncompatibleEvent }
  STATUS current
  DESCRIPTION
    "Node  with ip  firmware is incompatible"
  ::= { caNotifsGroup 185 }

nodeRebootedForYodaStuckNotif NOTIFICATION-TYPE
  OBJECTS { nodeRebootedForYodaStuckEvent }
  STATUS current
  DESCRIPTION
    "Node  with ip  is being rebooted as yoda is stuck"
  ::= { caNotifsGroup 186 }

protectionGroupSucceededNotif NOTIFICATION-TYPE
  OBJECTS { protectionGroupSucceededEvent }
  STATUS current
  DESCRIPTION
    "Backup run of protection group  of type  completed successfully"
  ::= { caNotifsGroup 187 }

unregisterExternalTargetFailedNotif NOTIFICATION-TYPE
  OBJECTS { unregisterExternalTargetFailedEvent }
  STATUS current
  DESCRIPTION
    "Unregistration for external target  failed."
  ::= { caNotifsGroup 188 }

licenseServerUnreachableNotif NOTIFICATION-TYPE
  OBJECTS { licenseServerUnreachableEvent }
  STATUS current
  DESCRIPTION
    "License server is unreachable."
  ::= { caNotifsGroup 189 }

invalidLicenseNotif NOTIFICATION-TYPE
  OBJECTS { invalidLicenseEvent }
  STATUS current
  DESCRIPTION
    "License is invalid."
  ::= { caNotifsGroup 190 }

unlicensedClusterNotif NOTIFICATION-TYPE
  OBJECTS { unlicensedClusterEvent }
  STATUS current
  DESCRIPTION
    "Cluster is unlicensed."
  ::= { caNotifsGroup 191 }

verifyRemoteClusterConnectionNotif NOTIFICATION-TYPE
  OBJECTS { verifyRemoteClusterConnectionEvent }
  STATUS current
  DESCRIPTION
    "Verify remote cluster connection and associated static route."
  ::= { caNotifsGroup 192 }

sysSrvcErrorsNotif NOTIFICATION-TYPE
  OBJECTS { sysSrvcErrorsEvent }
  STATUS current
  DESCRIPTION
    "Node  with ip  have errors in system service logs"
  ::= { caNotifsGroup 193 }

bridgeMigrationFailedNotif NOTIFICATION-TYPE
  OBJECTS { bridgeMigrationFailedEvent }
  STATUS current
  DESCRIPTION
    "Bridge Migrate failed on node  with ip "
  ::= { caNotifsGroup 194 }

bridgeMigrationRevertFailedNotif NOTIFICATION-TYPE
  OBJECTS { bridgeMigrationRevertFailedEvent }
  STATUS current
  DESCRIPTION
    "Bridge migration revert failed on node  with ip "
  ::= { caNotifsGroup 195 }

productModelInterfacesInconsistencyNotif NOTIFICATION-TYPE
  OBJECTS { productModelInterfacesInconsistencyEvent }
  STATUS current
  DESCRIPTION
    "Network interfaces inconsistency exists on cluster nodes. Network interfaces need to be consistent across nodes on same product model."
  ::= { caNotifsGroup 196 }

clusterInterfacesInconsistencyNotif NOTIFICATION-TYPE
  OBJECTS { clusterInterfacesInconsistencyEvent }
  STATUS current
  DESCRIPTION
    "Network interfaces inconsistency exists on different product models in heterogeneous cluster."
  ::= { caNotifsGroup 197 }

ntpServerUnReachableNotif NOTIFICATION-TYPE
  OBJECTS { ntpServerUnReachableEvent }
  STATUS current
  DESCRIPTION
    "NTP server is not reachable."
  ::= { caNotifsGroup 198 }

externalTargetNotReachableNotif NOTIFICATION-TYPE
  OBJECTS { externalTargetNotReachableEvent }
  STATUS current
  DESCRIPTION
    "External target  not reachable from node."
  ::= { caNotifsGroup 199 }

appInstanceUnhealthyNotif NOTIFICATION-TYPE
  OBJECTS { appInstanceUnhealthyEvent }
  STATUS current
  DESCRIPTION
    "Detected unhealthy instance  at "
  ::= { caNotifsGroup 200 }

indexingBacklogNotif NOTIFICATION-TYPE
  OBJECTS { indexingBacklogEvent }
  STATUS current
  DESCRIPTION
    "Backlog in indexing of VM contents."
  ::= { caNotifsGroup 201 }

searchNodeBusyNotif NOTIFICATION-TYPE
  OBJECTS { searchNodeBusyEvent }
  STATUS current
  DESCRIPTION
    "Search node is using more than 80% of cpu on machine."
  ::= { caNotifsGroup 202 }

nonEmptyUnmountedDirectoryNotif NOTIFICATION-TYPE
  OBJECTS { nonEmptyUnmountedDirectoryEvent }
  STATUS current
  DESCRIPTION
    "Unmounted directory is not empty, it has some entries."
  ::= { caNotifsGroup 203 }

rhinoUnhealthyNotif NOTIFICATION-TYPE
  OBJECTS { rhinoUnhealthyEvent }
  STATUS current
  DESCRIPTION
    "Too many Rhino healthchecks failed."
  ::= { caNotifsGroup 204 }

lessCPUCoreNotif NOTIFICATION-TYPE
  OBJECTS { lessCPUCoreEvent }
  STATUS current
  DESCRIPTION
    "Node  with ip  does not meet minimum CPU core count requirements"
  ::= { caNotifsGroup 205 }

licenseExpiredNotif NOTIFICATION-TYPE
  OBJECTS { licenseExpiredEvent }
  STATUS current
  DESCRIPTION
    "License has expired."
  ::= { caNotifsGroup 206 }

licenseAboutToExpireNotif NOTIFICATION-TYPE
  OBJECTS { licenseAboutToExpireEvent }
  STATUS current
  DESCRIPTION
    "License is about to expire."
  ::= { caNotifsGroup 207 }

biosAndBmcVersionMismatchNotif NOTIFICATION-TYPE
  OBJECTS { biosAndBmcVersionMismatchEvent }
  STATUS current
  DESCRIPTION
    "Node on the cluster has incompatible BIOS/BMC version"
  ::= { caNotifsGroup 208 }

unusedGflagsNotif NOTIFICATION-TYPE
  OBJECTS { unusedGflagsEvent }
  STATUS current
  DESCRIPTION
    "Node  with ip  has gflags that are no longer in use"
  ::= { caNotifsGroup 209 }

supportChannelAboutToCloseNotif NOTIFICATION-TYPE
  OBJECTS { supportChannelAboutToCloseEvent }
  STATUS current
  DESCRIPTION
    "Cohesity support channel about to close on cluster with ID "
  ::= { caNotifsGroup 210 }

licenseAccountOverUseNotif NOTIFICATION-TYPE
  OBJECTS { licenseAccountOverUseEvent }
  STATUS current
  DESCRIPTION
    "Licensed account is overused."
  ::= { caNotifsGroup 211 }

licenseIdentityInvalidNotif NOTIFICATION-TYPE
  OBJECTS { licenseIdentityInvalidEvent }
  STATUS current
  DESCRIPTION
    "License identity is invalid."
  ::= { caNotifsGroup 212 }

kMSCertificateWillExpireNotif NOTIFICATION-TYPE
  OBJECTS { kMSCertificateWillExpireEvent }
  STATUS current
  DESCRIPTION
    "A KMS server certificate will expire soon."
  ::= { caNotifsGroup 213 }

kMSCertificateExpirationNotif NOTIFICATION-TYPE
  OBJECTS { kMSCertificateExpirationEvent }
  STATUS current
  DESCRIPTION
    "A KMS server certificate has expired."
  ::= { caNotifsGroup 214 }

kMSErrorNotif NOTIFICATION-TYPE
  OBJECTS { kMSErrorEvent }
  STATUS current
  DESCRIPTION
    "An error was received while communicating with the key management server."
  ::= { caNotifsGroup 215 }

keyObjectCreatedNotif NOTIFICATION-TYPE
  OBJECTS { keyObjectCreatedEvent }
  STATUS current
  DESCRIPTION
    "A key object has been created."
  ::= { caNotifsGroup 216 }

keyObjectDestroyedNotif NOTIFICATION-TYPE
  OBJECTS { keyObjectDestroyedEvent }
  STATUS current
  DESCRIPTION
    "A key object has been destroyed."
  ::= { caNotifsGroup 217 }

kMSUnreachableNotif NOTIFICATION-TYPE
  OBJECTS { kMSUnreachableEvent }
  STATUS current
  DESCRIPTION
    "A KMS server is unreachable."
  ::= { caNotifsGroup 218 }

diskMarkedForRemovalNotif NOTIFICATION-TYPE
  OBJECTS { diskMarkedForRemovalEvent }
  STATUS current
  DESCRIPTION
    "Disk  marked for removal"
  ::= { caNotifsGroup 219 }

nodeMarkedForRemovalNotif NOTIFICATION-TYPE
  OBJECTS { nodeMarkedForRemovalEvent }
  STATUS current
  DESCRIPTION
    "Node is marked for removal from cluster"
  ::= { caNotifsGroup 220 }

addNodesStartedNotif NOTIFICATION-TYPE
  OBJECTS { addNodesStartedEvent }
  STATUS current
  DESCRIPTION
    "Node is joining the cluster"
  ::= { caNotifsGroup 221 }

diskRemovedNotif NOTIFICATION-TYPE
  OBJECTS { diskRemovedEvent }
  STATUS current
  DESCRIPTION
    "Disk  with serial  in slot  is removed from node  with ip "
  ::= { caNotifsGroup 222 }

sshKeyMismatchNotif NOTIFICATION-TYPE
  OBJECTS { sshKeyMismatchEvent }
  STATUS current
  DESCRIPTION
    "Check Failed : All nodes in the cluster must have same ssh keys!"
  ::= { caNotifsGroup 223 }

bMCModuleNotAvailableNotif NOTIFICATION-TYPE
  OBJECTS { bMCModuleNotAvailableEvent }
  STATUS current
  DESCRIPTION
    "BMC module is not available on node  with ip "
  ::= { caNotifsGroup 224 }

outOfMemoryRestartNotif NOTIFICATION-TYPE
  OBJECTS { outOfMemoryRestartEvent }
  STATUS current
  DESCRIPTION
    "Process  restarted due to out of memory"
  ::= { caNotifsGroup 225 }

metadataInstanceHasUnrecoverableErrorNotif NOTIFICATION-TYPE
  OBJECTS { metadataInstanceHasUnrecoverableErrorEvent }
  STATUS current
  DESCRIPTION
    "A corruption has been detected on disk "
  ::= { caNotifsGroup 226 }

metadataDiskRanOutOfSpaceNotif NOTIFICATION-TYPE
  OBJECTS { metadataDiskRanOutOfSpaceEvent }
  STATUS current
  DESCRIPTION
    "Scribe reservation increased failed"
  ::= { caNotifsGroup 227 }

licenseStatsHistoryCollectionNotif NOTIFICATION-TYPE
  OBJECTS { licenseStatsHistoryCollectionEvent }
  STATUS current
  DESCRIPTION
    "License stats history collection"
  ::= { caNotifsGroup 228 }

dnsServerConnectionFailedNotif NOTIFICATION-TYPE
  OBJECTS { dnsServerConnectionFailedEvent }
  STATUS current
  DESCRIPTION
    "DNS server is not reachable"
  ::= { caNotifsGroup 229 }

nASVaultIsFullNotif NOTIFICATION-TYPE
  OBJECTS { nASVaultIsFullEvent }
  STATUS current
  DESCRIPTION
    "NAS External target is full"
  ::= { caNotifsGroup 230 }

protectionGroupReplicationFailedNotif NOTIFICATION-TYPE
  OBJECTS { protectionGroupReplicationFailedEvent }
  STATUS current
  DESCRIPTION
    "Replication to remote cluster failed"
  ::= { caNotifsGroup 231 }

diskIdMismatchNotif NOTIFICATION-TYPE
  OBJECTS { diskIdMismatchEvent }
  STATUS current
  DESCRIPTION
    "Metadata Disk re-addition error due to improper disk removal, expected disk ID is different from saved disk ID"
  ::= { caNotifsGroup 232 }

continuousDataProtectionDisabledNotif NOTIFICATION-TYPE
  OBJECTS { continuousDataProtectionDisabledEvent }
  STATUS current
  DESCRIPTION
    "CDP is disabled for VM, Protection Group ID"
  ::= { caNotifsGroup 233 }

protectionPolicyDeletedNotif NOTIFICATION-TYPE
  OBJECTS { protectionPolicyDeletedEvent }
  STATUS current
  DESCRIPTION
    "Protection Policy was deleted"
  ::= { caNotifsGroup 234 }

objectBackupSlaViolatedNotif NOTIFICATION-TYPE
  OBJECTS { objectBackupSlaViolatedEvent }
  STATUS current
  DESCRIPTION
    "SLA for backup of object  is violated"
  ::= { caNotifsGroup 235 }

objectBackupFailedNotif NOTIFICATION-TYPE
  OBJECTS { objectBackupFailedEvent }
  STATUS current
  DESCRIPTION
    "Backup of  of type  failed with error "
  ::= { caNotifsGroup 236 }

auditLogFailureNotif NOTIFICATION-TYPE
  OBJECTS { auditLogFailureEvent }
  STATUS current
  DESCRIPTION
    "Cluster  is at risk of failing to process audit logs as required"
  ::= { caNotifsGroup 237 }

silicomNicFoundNotif NOTIFICATION-TYPE
  OBJECTS { silicomNicFoundEvent }
  STATUS current
  DESCRIPTION
    "Found Silicom NIC in node  wit ip "
  ::= { caNotifsGroup 238 }

diskRemovalCancelledNotif NOTIFICATION-TYPE
  OBJECTS { diskRemovalCancelledEvent }
  STATUS current
  DESCRIPTION
    "Disk removal is cancelled."
  ::= { caNotifsGroup 239 }

metadataMigrationsNotProgressingNotif NOTIFICATION-TYPE
  OBJECTS { metadataMigrationsNotProgressingEvent }
  STATUS current
  DESCRIPTION
    "Metadata migrations not progressing."
  ::= { caNotifsGroup 240 }

manualBackgroundSystemThrottlingAppliedNotif NOTIFICATION-TYPE
  OBJECTS { manualBackgroundSystemThrottlingAppliedEvent }
  STATUS current
  DESCRIPTION
    "Manual throttling of background system algorithms applied."
  ::= { caNotifsGroup 241 }

remoteStorageUsageHighNotif NOTIFICATION-TYPE
  OBJECTS { remoteStorageUsageHighEvent }
  STATUS current
  DESCRIPTION
    "Remote storage usage is high."
  ::= { caNotifsGroup 242 }

remoteStorageCapacityChangedNotif NOTIFICATION-TYPE
  OBJECTS { remoteStorageCapacityChangedEvent }
  STATUS current
  DESCRIPTION
    "Remote storage capacity has changed."
  ::= { caNotifsGroup 243 }

routingDaemonDownNotif NOTIFICATION-TYPE
  OBJECTS { routingDaemonDownEvent }
  STATUS current
  DESCRIPTION
    "Routing daemon is down."
  ::= { caNotifsGroup 244 }

remoteStorageManagementIpUnreachableNotif NOTIFICATION-TYPE
  OBJECTS { remoteStorageManagementIpUnreachableEvent }
  STATUS current
  DESCRIPTION
    "Remote storage Management IP is unreachable."
  ::= { caNotifsGroup 245 }

remoteStorageFileSystemMountFailedNotif NOTIFICATION-TYPE
  OBJECTS { remoteStorageFileSystemMountFailedEvent }
  STATUS current
  DESCRIPTION
    "Failed to mount NFS file system  from Pure Flash Array "
  ::= { caNotifsGroup 246 }

remoteStorageFileSystemDeletedNotif NOTIFICATION-TYPE
  OBJECTS { remoteStorageFileSystemDeletedEvent }
  STATUS current
  DESCRIPTION
    "File system  on Pure Flash Array  is deleted"
  ::= { caNotifsGroup 247 }

remoteStorageFileSystemUsageHighNotif NOTIFICATION-TYPE
  OBJECTS { remoteStorageFileSystemUsageHighEvent }
  STATUS current
  DESCRIPTION
    "Pure Flash Array  file system  usage is high"
  ::= { caNotifsGroup 248 }

nfsShareNotHealthyNotif NOTIFICATION-TYPE
  OBJECTS { nfsShareNotHealthyEvent }
  STATUS current
  DESCRIPTION
    "NFS share  with disk ID  mounted to node  with ip  is not healthy"
  ::= { caNotifsGroup 249 }

scribeBackgroundOpsStallingNotif NOTIFICATION-TYPE
  OBJECTS { scribeBackgroundOpsStallingEvent }
  STATUS current
  DESCRIPTION
    "Background ops are running for a longer time than expected"
  ::= { caNotifsGroup 250 }

eSDiskUsageExceedsThresholdNotif NOTIFICATION-TYPE
  OBJECTS { eSDiskUsageExceedsThresholdEvent }
  STATUS current
  DESCRIPTION
    "ES indices size on disk  is exceeding threshold."
  ::= { caNotifsGroup 251 }

dnsServerUnassignedNotif NOTIFICATION-TYPE
  OBJECTS { dnsServerUnassignedEvent }
  STATUS current
  DESCRIPTION
    "DNS server is not assigned on node  with IP "
  ::= { caNotifsGroup 252 }

insufficientResourcesToLaunchSysSrvPodNotif NOTIFICATION-TYPE
  OBJECTS { insufficientResourcesToLaunchSysSrvPodEvent }
  STATUS current
  DESCRIPTION
    "Failed to launch system service pos for instance  at  Application"
  ::= { caNotifsGroup 253 }

userDefaultPasswordNotif NOTIFICATION-TYPE
  OBJECTS { userDefaultPasswordEvent }
  STATUS current
  DESCRIPTION
    "Cluster  is using default password on node  with ip "
  ::= { caNotifsGroup 254 }

vMMigrationIdentifiedNotif NOTIFICATION-TYPE
  OBJECTS { vMMigrationIdentifiedEvent }
  STATUS current
  DESCRIPTION
    "Linked migrated VMs across vCenters."
  ::= { caNotifsGroup 255 }

wormChangeForGroupAlertNotif NOTIFICATION-TYPE
  OBJECTS { wormChangeForGroupAlertEvent }
  STATUS current
  DESCRIPTION
    "Cluster  is at potential security risk due to changes in  protection group settings"
  ::= { caNotifsGroup 256 }

wormChangeForPolicyAlertNotif NOTIFICATION-TYPE
  OBJECTS { wormChangeForPolicyAlertEvent }
  STATUS current
  DESCRIPTION
    "Cluster  is at potential security risk due to changes in  policy settings"
  ::= { caNotifsGroup 257 }

inconsistentInterfaceGroupSpeedNotif NOTIFICATION-TYPE
  OBJECTS { inconsistentInterfaceGroupSpeedEvent }
  STATUS current
  DESCRIPTION
    "Interface speed mismatch in a group."
  ::= { caNotifsGroup 258 }

atomNodeMemoryAboveThresholdNotif NOTIFICATION-TYPE
  OBJECTS { atomNodeMemoryAboveThresholdEvent }
  STATUS current
  DESCRIPTION
    "Atom node memory usage on  is above threshold(). Current memory, Max memory."
  ::= { caNotifsGroup 259 }

diskWithCorruptedPartitionTableNotif NOTIFICATION-TYPE
  OBJECTS { diskWithCorruptedPartitionTableEvent }
  STATUS current
  DESCRIPTION
    "VM with disks has a corrupted MBR/GPT partition table."
  ::= { caNotifsGroup 260 }

remoteStorageDataIpUnreachableNotif NOTIFICATION-TYPE
  OBJECTS { remoteStorageDataIpUnreachableEvent }
  STATUS current
  DESCRIPTION
    "Remote storage Data IP is unreachable."
  ::= { caNotifsGroup 261 }

nodeTcpOrphanConnectionsExceededNotif NOTIFICATION-TYPE
  OBJECTS { nodeTcpOrphanConnectionsExceededEvent }
  STATUS current
  DESCRIPTION
    "TCP orphan connections exceeded the threshold."
  ::= { caNotifsGroup 262 }

appNetworkMasterUnhealthyNotif NOTIFICATION-TYPE
  OBJECTS { appNetworkMasterUnhealthyEvent }
  STATUS current
  DESCRIPTION
    "App Network Master status is unhealthy"
  ::= { caNotifsGroup 263 }

appNetworkNodeUnhealthyNotif NOTIFICATION-TYPE
  OBJECTS { appNetworkNodeUnhealthyEvent }
  STATUS current
  DESCRIPTION
    "Node  App Network Node status is unhealthy"
  ::= { caNotifsGroup 264 }

lowReplicationFactorNotif NOTIFICATION-TYPE
  OBJECTS { lowReplicationFactorEvent }
  STATUS current
  DESCRIPTION
    " cluster is on Replication Factor 1 There is no resiliency to handle disk failure!"
  ::= { caNotifsGroup 265 }

duplicateIpDetectedNotif NOTIFICATION-TYPE
  OBJECTS { duplicateIpDetectedEvent }
  STATUS current
  DESCRIPTION
    "Duplicate IP detected in  with ip "
  ::= { caNotifsGroup 266 }

powerSupplyAcRestoredNotif NOTIFICATION-TYPE
  OBJECTS { powerSupplyAcRestoredEvent }
  STATUS current
  DESCRIPTION
    "Power Supply Ac restored"
  ::= { caNotifsGroup 267 }

remoteClusterNotReachableNotif NOTIFICATION-TYPE
  OBJECTS { remoteClusterNotReachableEvent }
  STATUS current
  DESCRIPTION
    "Remote cluster is not reachable from cluster."
  ::= { caNotifsGroup 268 }

remoteStorageUnexpectedNfsExportRulesNotif NOTIFICATION-TYPE
  OBJECTS { remoteStorageUnexpectedNfsExportRulesEvent }
  STATUS current
  DESCRIPTION
    "NFS export rule mismatch on Pure FlashBlade  file system "
  ::= { caNotifsGroup 269 }

unregisteredClusterNotif NOTIFICATION-TYPE
  OBJECTS { unregisteredClusterEvent }
  STATUS current
  DESCRIPTION
    "Cluster is unregistered."
  ::= { caNotifsGroup 270 }

clusterPendingAuditReportUploadNotif NOTIFICATION-TYPE
  OBJECTS { clusterPendingAuditReportUploadEvent }
  STATUS current
  DESCRIPTION
    "Audit report is due."
  ::= { caNotifsGroup 271 }

appNetworkResourceUnhealthyNotif NOTIFICATION-TYPE
  OBJECTS { appNetworkResourceUnhealthyEvent }
  STATUS current
  DESCRIPTION
    "App Network Resources status is unhealthy"
  ::= { caNotifsGroup 272 }

entityWithTooManyOpenHandlesNotif NOTIFICATION-TYPE
  OBJECTS { entityWithTooManyOpenHandlesEvent }
  STATUS current
  DESCRIPTION
    "There are too many open handles for the same entity"
  ::= { caNotifsGroup 273 }

viewSlowProtocolOpNotif NOTIFICATION-TYPE
  OBJECTS { viewSlowProtocolOpEvent }
  STATUS current
  DESCRIPTION
    "Slow operation detected from view"
  ::= { caNotifsGroup 274 }

policyDatalockDurationChangedNotif NOTIFICATION-TYPE
  OBJECTS { policyDatalockDurationChangedEvent }
  STATUS current
  DESCRIPTION
    "Protection policy datalock duration changed."
  ::= { caNotifsGroup 275 }

protectionPolicyModifiedNotif NOTIFICATION-TYPE
  OBJECTS { protectionPolicyModifiedEvent }
  STATUS current
  DESCRIPTION
    "Protection policy modified."
  ::= { caNotifsGroup 276 }

protectionGroupModifiedNotif NOTIFICATION-TYPE
  OBJECTS { protectionGroupModifiedEvent }
  STATUS current
  DESCRIPTION
    "Protection group modified."
  ::= { caNotifsGroup 277 }

protectionRunModifiedNotif NOTIFICATION-TYPE
  OBJECTS { protectionRunModifiedEvent }
  STATUS current
  DESCRIPTION
    "Protection run modified."
  ::= { caNotifsGroup 278 }

viewFailoverDuplicateViewUIDNotif NOTIFICATION-TYPE
  OBJECTS { viewFailoverDuplicateViewUIDEvent }
  STATUS current
  DESCRIPTION
    "Multiple views exist on the cluster with same universal view id"
  ::= { caNotifsGroup 279 }

viewFailoverReplicationFailedNotif NOTIFICATION-TYPE
  OBJECTS { viewFailoverReplicationFailedEvent }
  STATUS current
  DESCRIPTION
    "Replication for planned failover of view  failed"
  ::= { caNotifsGroup 280 }

viewFailoverStuckNotif NOTIFICATION-TYPE
  OBJECTS { viewFailoverStuckEvent }
  STATUS current
  DESCRIPTION
    "Planned failover of view  is stuck"
  ::= { caNotifsGroup 281 }

viewFailoverFailedNotif NOTIFICATION-TYPE
  OBJECTS { viewFailoverFailedEvent }
  STATUS current
  DESCRIPTION
    "Unsuccessful failover of view "
  ::= { caNotifsGroup 282 }

viewFailoverStateUpdateFailedNotif NOTIFICATION-TYPE
  OBJECTS { viewFailoverStateUpdateFailedEvent }
  STATUS current
  DESCRIPTION
    "Update of state maintained for failover of view  failed"
  ::= { caNotifsGroup 283 }

vaultConfigValidationFailedNotif NOTIFICATION-TYPE
  OBJECTS { vaultConfigValidationFailedEvent }
  STATUS current
  DESCRIPTION
    "Config validation failed for the vault."
  ::= { caNotifsGroup 284 }

remoteReplicationTrackingViewUpdateFailedNotif NOTIFICATION-TYPE
  OBJECTS { remoteReplicationTrackingViewUpdateFailedEvent }
  STATUS current
  DESCRIPTION
    "Update of tracking view for replication failed"
  ::= { caNotifsGroup 285 }

remoteIndexingFallbackNotif NOTIFICATION-TYPE
  OBJECTS { remoteIndexingFallbackEvent }
  STATUS current
  DESCRIPTION
    "Remote indexing for volume has failed. Falling back to local indexing."
  ::= { caNotifsGroup 286 }

archiveObjectGCFailedAlertNotif NOTIFICATION-TYPE
  OBJECTS { archiveObjectGCFailedAlertEvent }
  STATUS current
  DESCRIPTION
    "Archive object  garbage collection in external target  failed."
  ::= { caNotifsGroup 287 }

highRPCLatenciesNotif NOTIFICATION-TYPE
  OBJECTS { highRPCLatenciesEvent }
  STATUS current
  DESCRIPTION
    "RPC latencies for metadata service between node  and  are high, mean latency of  usecs has been observed. Latencies were measured over a  secs."
  ::= { caNotifsGroup 288 }

unexpectedIpAddressNotif NOTIFICATION-TYPE
  OBJECTS { unexpectedIpAddressEvent }
  STATUS current
  DESCRIPTION
    "Unexpected IP Address in an interface."
  ::= { caNotifsGroup 289 }

policyDatalockChangedNotif NOTIFICATION-TYPE
  OBJECTS { policyDatalockChangedEvent }
  STATUS current
  DESCRIPTION
    "Datalock was  for policy  and  target"
  ::= { caNotifsGroup 290 }

protectionGroupDeletedNotif NOTIFICATION-TYPE
  OBJECTS { protectionGroupDeletedEvent }
  STATUS current
  DESCRIPTION
    "Protection Group was deleted"
  ::= { caNotifsGroup 291 }

sourceConnectivityFailureNotif NOTIFICATION-TYPE
  OBJECTS { sourceConnectivityFailureEvent }
  STATUS current
  DESCRIPTION
    "Failure in source connectivity verification."
  ::= { caNotifsGroup 292 }

diskOkToRemoveNotif NOTIFICATION-TYPE
  OBJECTS { diskOkToRemoveEvent }
  STATUS current
  DESCRIPTION
    "Disk is OK to remove."
  ::= { caNotifsGroup 293 }

systemServiceAppInstallationFailedNotif NOTIFICATION-TYPE
  OBJECTS { systemServiceAppInstallationFailedEvent }
  STATUS current
  DESCRIPTION
    "Failed to install System service"
  ::= { caNotifsGroup 294 }

nexusFaultIsolationRecoveryNotif NOTIFICATION-TYPE
  OBJECTS { nexusFaultIsolationRecoveryEvent }
  STATUS current
  DESCRIPTION
    "Nexus executing recovery actions."
  ::= { caNotifsGroup 295 }

continuousDataProtectionAlertNotif NOTIFICATION-TYPE
  OBJECTS { continuousDataProtectionAlertEvent }
  STATUS current
  DESCRIPTION
    "Alert is raised for CDP VM entity, Protection Group ID"
  ::= { caNotifsGroup 296 }

hostShellAccessExpiryNotif NOTIFICATION-TYPE
  OBJECTS { hostShellAccessExpiryEvent }
  STATUS current
  DESCRIPTION
    "Host shell access is about to expire"
  ::= { caNotifsGroup 297 }

bucketMetadataModifiedNotif NOTIFICATION-TYPE
  OBJECTS { bucketMetadataModifiedEvent }
  STATUS current
  DESCRIPTION
    "Metadata  of  view  modified"
  ::= { caNotifsGroup 298 }

bucketACLUpdatedNotif NOTIFICATION-TYPE
  OBJECTS { bucketACLUpdatedEvent }
  STATUS current
  DESCRIPTION
    "Access Control List of S3 view  updated"
  ::= { caNotifsGroup 299 }

bucketCreatedNotif NOTIFICATION-TYPE
  OBJECTS { bucketCreatedEvent }
  STATUS current
  DESCRIPTION
    "New  view with name  is created"
  ::= { caNotifsGroup 300 }

bucketDeletedNotif NOTIFICATION-TYPE
  OBJECTS { bucketDeletedEvent }
  STATUS current
  DESCRIPTION
    " view with name  is deleted"
  ::= { caNotifsGroup 301 }

serviceGflagsChangedNotif NOTIFICATION-TYPE
  OBJECTS { serviceGflagsChangedEvent }
  STATUS current
  DESCRIPTION
    "Service gflags changed notification."
  ::= { caNotifsGroup 302 }

algorithmFrequentlyTimeOutAlertNotif NOTIFICATION-TYPE
  OBJECTS { algorithmFrequentlyTimeOutAlertEvent }
  STATUS current
  DESCRIPTION
    "An algorithm is frequently timing out and is behind schedule for a long time."
  ::= { caNotifsGroup 303 }

successfulFailoverOpAlertNotif NOTIFICATION-TYPE
  OBJECTS { successfulFailoverOpAlertEvent }
  STATUS current
  DESCRIPTION
    "Failover operation triggered from cluster  using runbook  is successful."
  ::= { caNotifsGroup 304 }

successfulFailbackOpAlertNotif NOTIFICATION-TYPE
  OBJECTS { successfulFailbackOpAlertEvent }
  STATUS current
  DESCRIPTION
    "Failback operation triggered from cluster  using runbook  is successful."
  ::= { caNotifsGroup 305 }

successfulTestAndDevOpAlertNotif NOTIFICATION-TYPE
  OBJECTS { successfulTestAndDevOpAlertEvent }
  STATUS current
  DESCRIPTION
    "Test and Dev operation triggered from cluster  using runbook  is successful."
  ::= { caNotifsGroup 306 }

successfulPrepareFailbackOpAlertNotif NOTIFICATION-TYPE
  OBJECTS { successfulPrepareFailbackOpAlertEvent }
  STATUS current
  DESCRIPTION
    "Prepare failback operation triggered from cluster  using runbook  is successful."
  ::= { caNotifsGroup 307 }

successfulTeardownOpAlertNotif NOTIFICATION-TYPE
  OBJECTS { successfulTeardownOpAlertEvent }
  STATUS current
  DESCRIPTION
    "Teardown operation triggered from cluster  using runbook  is successful."
  ::= { caNotifsGroup 308 }

failedFailoverOpAlertNotif NOTIFICATION-TYPE
  OBJECTS { failedFailoverOpAlertEvent }
  STATUS current
  DESCRIPTION
    "Failover operation triggered from cluster  using runbook  has failed."
  ::= { caNotifsGroup 309 }

failedFailbackOpAlertNotif NOTIFICATION-TYPE
  OBJECTS { failedFailbackOpAlertEvent }
  STATUS current
  DESCRIPTION
    "Failback operation triggered from cluster  using runbook  has failed."
  ::= { caNotifsGroup 310 }

failedTestAndDevOpAlertNotif NOTIFICATION-TYPE
  OBJECTS { failedTestAndDevOpAlertEvent }
  STATUS current
  DESCRIPTION
    "Test and Dev operation triggered from cluster  using runbook  has failed."
  ::= { caNotifsGroup 311 }

failedPrepareFailbackOpAlertNotif NOTIFICATION-TYPE
  OBJECTS { failedPrepareFailbackOpAlertEvent }
  STATUS current
  DESCRIPTION
    "Prepare failback operation triggered from cluster  using runbook  has failed."
  ::= { caNotifsGroup 312 }

failedTeardownOpAlertNotif NOTIFICATION-TYPE
  OBJECTS { failedTeardownOpAlertEvent }
  STATUS current
  DESCRIPTION
    "Teardown operation triggered from cluster  using runbook  has failed."
  ::= { caNotifsGroup 313 }

ssdMediaErrorNotif NOTIFICATION-TYPE
  OBJECTS { ssdMediaErrorEvent }
  STATUS current
  DESCRIPTION
    "Ssd Media Error"
  ::= { caNotifsGroup 314 }

diskNeedFirmwareUpgradeNotif NOTIFICATION-TYPE
  OBJECTS { diskNeedFirmwareUpgradeEvent }
  STATUS current
  DESCRIPTION
    "Disk ID  needs firmware upgrade on the node  with ip ."
  ::= { caNotifsGroup 315 }

metadataMovedToFlashbladeNotif NOTIFICATION-TYPE
  OBJECTS { metadataMovedToFlashbladeEvent }
  STATUS current
  DESCRIPTION
    "All the metadata has moved to the flashblade."
  ::= { caNotifsGroup 316 }

viewCloneMetadataBloatNotif NOTIFICATION-TYPE
  OBJECTS { viewCloneMetadataBloatEvent }
  STATUS current
  DESCRIPTION
    "Too many unflushed records in metadata data journal for  during cloning"
  ::= { caNotifsGroup 317 }

chunkFileContainerInconsistencyNotif NOTIFICATION-TYPE
  OBJECTS { chunkFileContainerInconsistencyEvent }
  STATUS current
  DESCRIPTION
    "Chunk File Container inconsistency, cluster internal error that requires action by Cohesity Support"
  ::= { caNotifsGroup 318 }

apolloIssuedActionVersionMismatchNotif NOTIFICATION-TYPE
  OBJECTS { apolloIssuedActionVersionMismatchEvent }
  STATUS current
  DESCRIPTION
    "Apollo is issuing action(s) with API version . Action was ignored by bridge since it expects an API version of ."
  ::= { caNotifsGroup 319 }

networkStatsIsNotNormalNotif NOTIFICATION-TYPE
  OBJECTS { networkStatsIsNotNormalEvent }
  STATUS current
  DESCRIPTION
    "Node  with ip  netstats is not normal."
  ::= { caNotifsGroup 320 }

highClusterUtilizationNotif NOTIFICATION-TYPE
  OBJECTS { highClusterUtilizationEvent }
  STATUS current
  DESCRIPTION
    "Cluster utilization is high (>=85%)."
  ::= { caNotifsGroup 321 }

createSnapshotSucceededNotif NOTIFICATION-TYPE
  OBJECTS { createSnapshotSucceededEvent }
  STATUS current
  DESCRIPTION
    "Create Snapshot version  succeeded on the cluster"
  ::= { caNotifsGroup 322 }

nodeConnectivityFailedNotif NOTIFICATION-TYPE
  OBJECTS { nodeConnectivityFailedEvent }
  STATUS current
  DESCRIPTION
    "Node  with IP  connection failure to ."
  ::= { caNotifsGroup 323 }

deferScheduleNotif NOTIFICATION-TYPE
  OBJECTS { deferScheduleEvent }
  STATUS current
  DESCRIPTION
    "Deferred schedule for  to resolve conflicts among multiple schedules for  with id "
  ::= { caNotifsGroup 324 }

cloudDataOpFailureNotif NOTIFICATION-TYPE
  OBJECTS { cloudDataOpFailureEvent }
  STATUS current
  DESCRIPTION
    "Cloud operation failures detected on external target "
  ::= { caNotifsGroup 325 }

objectStorePortalInitializationFailureNotif NOTIFICATION-TYPE
  OBJECTS { objectStorePortalInitializationFailureEvent }
  STATUS current
  DESCRIPTION
    "Bridge S3 Http Server failed to initialize with reason "
  ::= { caNotifsGroup 326 }

kubernetesObjectsCleanupAlertNotif NOTIFICATION-TYPE
  OBJECTS { kubernetesObjectsCleanupAlertEvent }
  STATUS current
  DESCRIPTION
    "Failed to cleanup kubernetes objects on stale incarnation id"
  ::= { caNotifsGroup 327 }

nodeNotPresentInKubernetesClusterNotif NOTIFICATION-TYPE
  OBJECTS { nodeNotPresentInKubernetesClusterEvent }
  STATUS current
  DESCRIPTION
    "Node(s) [  ] are not part of kubernetes cluster"
  ::= { caNotifsGroup 328 }

objectDeletionRejectedNotif NOTIFICATION-TYPE
  OBJECTS { objectDeletionRejectedEvent }
  STATUS current
  DESCRIPTION
    "Could not delete objects in the run before run expiry. They will be deleted when the run snapshot is expired. Protection Group ID. Backup Type. Run id."
  ::= { caNotifsGroup 329 }

rpmPackageVersionMismatchedNotif NOTIFICATION-TYPE
  OBJECTS { rpmPackageVersionMismatchedEvent }
  STATUS current
  DESCRIPTION
    "Rpm package version mismatched on the node  with ip "
  ::= { caNotifsGroup 330 }

baseOSVersionMismatchedNotif NOTIFICATION-TYPE
  OBJECTS { baseOSVersionMismatchedEvent }
  STATUS current
  DESCRIPTION
    "BaseOS version mismatched on the node  with ip "
  ::= { caNotifsGroup 331 }

createSnapshotFailedNotif NOTIFICATION-TYPE
  OBJECTS { createSnapshotFailedEvent }
  STATUS current
  DESCRIPTION
    "Create Snapshot version  failed on the cluster"
  ::= { caNotifsGroup 332 }

restoreSnapshotStartedNotif NOTIFICATION-TYPE
  OBJECTS { restoreSnapshotStartedEvent }
  STATUS current
  DESCRIPTION
    "Restore Snapshot version  started on the cluster"
  ::= { caNotifsGroup 333 }

restoreSnapshotSucceededNotif NOTIFICATION-TYPE
  OBJECTS { restoreSnapshotSucceededEvent }
  STATUS current
  DESCRIPTION
    "Restore Snapshot version  succeeded on the cluster"
  ::= { caNotifsGroup 334 }

restoreSnapshotFailedNotif NOTIFICATION-TYPE
  OBJECTS { restoreSnapshotFailedEvent }
  STATUS current
  DESCRIPTION
    "Restore Snapshot version  failed on the cluster"
  ::= { caNotifsGroup 335 }

createSnapshotStartedNotif NOTIFICATION-TYPE
  OBJECTS { createSnapshotStartedEvent }
  STATUS current
  DESCRIPTION
    "Create Snapshot version  started on the cluster"
  ::= { caNotifsGroup 336 }

principalWithNonViewerRoleNotif NOTIFICATION-TYPE
  OBJECTS { principalWithNonViewerRoleEvent }
  STATUS current
  DESCRIPTION
    " cluster has one or more iris principals with roles other than viewer"
  ::= { caNotifsGroup 337 }

azureCEHostCachingEnabledNotif NOTIFICATION-TYPE
  OBJECTS { azureCEHostCachingEnabledEvent }
  STATUS current
  DESCRIPTION
    "In case of Azure Cloud Edition clusters if Host Caching is not set to 'None' on Azure nodes/VMs then it might lead to potential data loss. Disks that have Host caching not set to 'None' are on node"
  ::= { caNotifsGroup 338 }

recentLogBeingRotatedNotif NOTIFICATION-TYPE
  OBJECTS { recentLogBeingRotatedEvent }
  STATUS current
  DESCRIPTION
    " log in  hours rotated on node  "
  ::= { caNotifsGroup 339 }

repeatedlyFailingShardAlertNotif NOTIFICATION-TYPE
  OBJECTS { repeatedlyFailingShardAlertEvent }
  STATUS current
  DESCRIPTION
    "Background tasks have hit a slowness issue because Apollo shards are failing more often than expected."
  ::= { caNotifsGroup 340 }

backlogDuringBlackOutNotif NOTIFICATION-TYPE
  OBJECTS { backlogDuringBlackOutEvent }
  STATUS current
  DESCRIPTION
    "Apollo is in backlog state for more than a threshold number of days during the blackout window auto-scheduling."
  ::= { caNotifsGroup 341 }

timeConsumingShardAlertNotif NOTIFICATION-TYPE
  OBJECTS { timeConsumingShardAlertEvent }
  STATUS current
  DESCRIPTION
    "Apollo shard runtime is greater than the average value by a threshold."
  ::= { caNotifsGroup 342 }

highNonDedupToDedupPercentNotif NOTIFICATION-TYPE
  OBJECTS { highNonDedupToDedupPercentEvent }
  STATUS current
  DESCRIPTION
    "High non-dedup to dedup percent observed in inline dedup Storage domain . This could lead to higher than expected cluster space usage."
  ::= { caNotifsGroup 343 }

appsModeDisabledDueToSubnetClashNotif NOTIFICATION-TYPE
  OBJECTS { appsModeDisabledDueToSubnetClashEvent }
  STATUS current
  DESCRIPTION
    "Apps mode & Marketplace apps mode are disabled due to a subnet clash. To fix, update new subnet for apps, through edit cluster settings page(Settings->Summary->Configure->Configure Apps management network). Also enable marketplace apps mode if needed."
  ::= { caNotifsGroup 344 }

oracleMountFailureNotif NOTIFICATION-TYPE
  OBJECTS { oracleMountFailureEvent }
  STATUS current
  DESCRIPTION
    "If there are some mount failures, it will affect the backup/restore performance. Mount could fail because of many reasons like stale mount, incorrect mount options, e.t.c"
  ::= { caNotifsGroup 345 }

protectionServiceNotInitializedNotif NOTIFICATION-TYPE
  OBJECTS { protectionServiceNotInitializedEvent }
  STATUS current
  DESCRIPTION
    "Protection Service is not initialized"
  ::= { caNotifsGroup 346 }

fragmentActionsRepeatedlyFailingAlertNotif NOTIFICATION-TYPE
  OBJECTS { fragmentActionsRepeatedlyFailingAlertEvent }
  STATUS current
  DESCRIPTION
    "Many background actions in Apollo are hitting unexpected errors."
  ::= { caNotifsGroup 347 }

userTuningsStuckAlertIdNotif NOTIFICATION-TYPE
  OBJECTS { userTuningsStuckAlertIdEvent }
  STATUS current
  DESCRIPTION
    "User tuned gflags are not set/cleared on time."
  ::= { caNotifsGroup 348 }

kBrickMetadataInconsistentStateNotif NOTIFICATION-TYPE
  OBJECTS { kBrickMetadataInconsistentStateEvent }
  STATUS current
  DESCRIPTION
    "Chunk mapping for chunk  in brick with leaf node id  is in inconsistent state"
  ::= { caNotifsGroup 349 }

eCConversionBackloggedNotif NOTIFICATION-TYPE
  OBJECTS { eCConversionBackloggedEvent }
  STATUS current
  DESCRIPTION
    "Old un-encoded chunk file  observed in Storage domain . Erasure coding algorithm is backlogged. This could lead to higher than expected cluster space usage."
  ::= { caNotifsGroup 350 }

diskSwappedNotif NOTIFICATION-TYPE
  OBJECTS { diskSwappedEvent }
  STATUS current
  DESCRIPTION
    "Disk with id  and serial  on node  with ip  is swapped from node "
  ::= { caNotifsGroup 351 }

remoteStorageConfigureFailedNotif NOTIFICATION-TYPE
  OBJECTS { remoteStorageConfigureFailedEvent }
  STATUS current
  DESCRIPTION
    "Failed to configure remote storage"
  ::= { caNotifsGroup 352 }

aVHighRequestQueueSizeNotif NOTIFICATION-TYPE
  OBJECTS { aVHighRequestQueueSizeEvent }
  STATUS current
  DESCRIPTION
    "Antivirus scan queue is too long"
  ::= { caNotifsGroup 353 }

aVHighResponseTimeNotif NOTIFICATION-TYPE
  OBJECTS { aVHighResponseTimeEvent }
  STATUS current
  DESCRIPTION
    "Antivirus scan slowness is detected"
  ::= { caNotifsGroup 354 }

orphanEntityValueVersionMismatchNotif NOTIFICATION-TYPE
  OBJECTS { orphanEntityValueVersionMismatchEvent }
  STATUS current
  DESCRIPTION
    "Cluster  might have an error that requires action by Cohesity Support"
  ::= { caNotifsGroup 355 }

heavyFileOperationContentionNotif NOTIFICATION-TYPE
  OBJECTS { heavyFileOperationContentionEvent }
  STATUS current
  DESCRIPTION
    "Operation on the same file has been too heavy and rejected"
  ::= { caNotifsGroup 356 }

verifyNonExistentBrickFailedNotif NOTIFICATION-TYPE
  OBJECTS { verifyNonExistentBrickFailedEvent }
  STATUS current
  DESCRIPTION
    "Verify Non Existent Brick failed, cluster internal error that requires action by Cohesity Support"
  ::= { caNotifsGroup 357 }

chunkMigrationVerifyChunkInCfmFailedNotif NOTIFICATION-TYPE
  OBJECTS { chunkMigrationVerifyChunkInCfmFailedEvent }
  STATUS current
  DESCRIPTION
    "Chunk Migration failed, cluster internal error that requires action by Cohesity Support"
  ::= { caNotifsGroup 358 }

chunkMigrationVerifyBrickOwnedNDDChunksFailedNotif NOTIFICATION-TYPE
  OBJECTS { chunkMigrationVerifyBrickOwnedNDDChunksFailedEvent }
  STATUS current
  DESCRIPTION
    "Chunk Migration failed, cluster internal error that requires action by Cohesity Support"
  ::= { caNotifsGroup 359 }

gCStalledAlertNotif NOTIFICATION-TYPE
  OBJECTS { gCStalledAlertEvent }
  STATUS current
  DESCRIPTION
    "Garbage collection has stalled on the cluster. Please contact customer support immediately. If corrective action is not taken, the cluster will run out of space causing an outage."
  ::= { caNotifsGroup 360 }

upgradeCancelledNotif NOTIFICATION-TYPE
  OBJECTS { upgradeCancelledEvent }
  STATUS current
  DESCRIPTION
    "Upgrade to target version  canceled from the node  with ip "
  ::= { caNotifsGroup 361 }

oracleRestoreChainBreakNotif NOTIFICATION-TYPE
  OBJECTS { oracleRestoreChainBreakEvent }
  STATUS current
  DESCRIPTION
    "Oracle Restore Chain Break."
  ::= { caNotifsGroup 362 }

nasSourceSnapshotDeletionFailedNotif NOTIFICATION-TYPE
  OBJECTS { nasSourceSnapshotDeletionFailedEvent }
  STATUS current
  DESCRIPTION
    "Deletion of NAS source's native snapshot failed. This was created by Cohesity to perform backup, please delete it as it is not required anymore."
  ::= { caNotifsGroup 363 }

isilonChangelistCleanupFailedNotif NOTIFICATION-TYPE
  OBJECTS { isilonChangelistCleanupFailedEvent }
  STATUS current
  DESCRIPTION
    "Deletion of the cohesity created changelist failed, most likely due to transient errors. This was created by Cohesity to perform backup, please delete it as it is not required anymore."
  ::= { caNotifsGroup 364 }

nodeRemovalStuckNotif NOTIFICATION-TYPE
  OBJECTS { nodeRemovalStuckEvent }
  STATUS current
  DESCRIPTION
    "Removal is stuck for Node with id"
  ::= { caNotifsGroup 365 }

diskRemovalStuckNotif NOTIFICATION-TYPE
  OBJECTS { diskRemovalStuckEvent }
  STATUS current
  DESCRIPTION
    "Removal is stuck for Disk with id"
  ::= { caNotifsGroup 366 }

kMSFailoverNotif NOTIFICATION-TYPE
  OBJECTS { kMSFailoverEvent }
  STATUS current
  DESCRIPTION
    "KMS  with version  in cluster  has failed over to backup server"
  ::= { caNotifsGroup 367 }

restoreTaskWarningNotif NOTIFICATION-TYPE
  OBJECTS { restoreTaskWarningEvent }
  STATUS current
  DESCRIPTION
    "Restore for object  in job  succeeded with warnings"
  ::= { caNotifsGroup 368 }

restoreTaskFailedNotif NOTIFICATION-TYPE
  OBJECTS { restoreTaskFailedEvent }
  STATUS current
  DESCRIPTION
    "Restore for object  in job  failed"
  ::= { caNotifsGroup 369 }

overwriteThrottlingScheduleAlertNotif NOTIFICATION-TYPE
  OBJECTS { overwriteThrottlingScheduleAlertEvent }
  STATUS current
  DESCRIPTION
    "A backlog in background clean up task was observed. Once cluster utilization becomes high, its priority will be increased which could create delays in the SmartFiles workloads. Kindly contact Cohesity support in case such delays in the SmartFiles workloads are experienced."
  ::= { caNotifsGroup 370 }

uIUserLockoutNotif NOTIFICATION-TYPE
  OBJECTS { uIUserLockoutEvent }
  STATUS current
  DESCRIPTION
    "UI User Locked out"
  ::= { caNotifsGroup 371 }

uILoginFailureNotif NOTIFICATION-TYPE
  OBJECTS { uILoginFailureEvent }
  STATUS current
  DESCRIPTION
    "UI Login failed"
  ::= { caNotifsGroup 372 }

uILoginSuccessNotif NOTIFICATION-TYPE
  OBJECTS { uILoginSuccessEvent }
  STATUS current
  DESCRIPTION
    "UI Login is successful"
  ::= { caNotifsGroup 373 }

inactivityUITimeoutChangedNotif NOTIFICATION-TYPE
  OBJECTS { inactivityUITimeoutChangedEvent }
  STATUS current
  DESCRIPTION
    "UI Inactivity Timeout Changed"
  ::= { caNotifsGroup 374 }

absoluteUITimeoutChangedNotif NOTIFICATION-TYPE
  OBJECTS { absoluteUITimeoutChangedEvent }
  STATUS current
  DESCRIPTION
    "UI Absolute Timeout Changed"
  ::= { caNotifsGroup 375 }

sSHLoginSuccessNotif NOTIFICATION-TYPE
  OBJECTS { sSHLoginSuccessEvent }
  STATUS current
  DESCRIPTION
    "UI Login is successful"
  ::= { caNotifsGroup 376 }

sSHLoginFailureNotif NOTIFICATION-TYPE
  OBJECTS { sSHLoginFailureEvent }
  STATUS current
  DESCRIPTION
    "UI Login failed"
  ::= { caNotifsGroup 377 }

clusterServicesManuallyStoppedNotif NOTIFICATION-TYPE
  OBJECTS { clusterServicesManuallyStoppedEvent }
  STATUS current
  DESCRIPTION
    "Cluster Services Manually Stopped."
  ::= { caNotifsGroup 378 }

clusterServicesManuallyStartedNotif NOTIFICATION-TYPE
  OBJECTS { clusterServicesManuallyStartedEvent }
  STATUS current
  DESCRIPTION
    "Cluster Services Manually Started."
  ::= { caNotifsGroup 379 }

cloneBackupCleanupIssuesNotif NOTIFICATION-TYPE
  OBJECTS { cloneBackupCleanupIssuesEvent }
  STATUS current
  DESCRIPTION
    "Cleanup for clone backup dir  has failed."
  ::= { caNotifsGroup 380 }

tenantIndexingConfigMissingNotif NOTIFICATION-TYPE
  OBJECTS { tenantIndexingConfigMissingEvent }
  STATUS current
  DESCRIPTION
    "Tenant Indexing cloud config is missing."
  ::= { caNotifsGroup 381 }

staleDirsFoundInYodaCloneBackupViewsNotif NOTIFICATION-TYPE
  OBJECTS { staleDirsFoundInYodaCloneBackupViewsEvent }
  STATUS current
  DESCRIPTION
    "Manual cleanup of yoda clone backup views is needed to improve indexing speed."
  ::= { caNotifsGroup 382 }

archiveValidationFailedAlertNotif NOTIFICATION-TYPE
  OBJECTS { archiveValidationFailedAlertEvent }
  STATUS current
  DESCRIPTION
    "Cohesity has determined an inconsistency in an archive created on the external target "
  ::= { caNotifsGroup 383 }

remoteReplicationEncryptionKeyMismatchNotif NOTIFICATION-TYPE
  OBJECTS { remoteReplicationEncryptionKeyMismatchEvent }
  STATUS current
  DESCRIPTION
    "Mismatch in encryption key for replication to remote cluster "
  ::= { caNotifsGroup 384 }

morphedGarbageThresholdExceededAlertNotif NOTIFICATION-TYPE
  OBJECTS { morphedGarbageThresholdExceededAlertEvent }
  STATUS current
  DESCRIPTION
    "Imbalance threshold exceeded for chunkfiles in cluster , partition , This can cause increase in the cluster usage"
  ::= { caNotifsGroup 385 }

switchedToSpaceModeNotif NOTIFICATION-TYPE
  OBJECTS { switchedToSpaceModeEvent }
  STATUS current
  DESCRIPTION
    "Metadata is moving to space conserve mode. This may have a significantly adverse effect on performance. Please add more metadata space for better performance."
  ::= { caNotifsGroup 386 }

imbalanceThresholdExceededAlertNotif NOTIFICATION-TYPE
  OBJECTS { imbalanceThresholdExceededAlertEvent }
  STATUS current
  DESCRIPTION
    "Imbalance threshold exceeded for chunkfiles in cluster , partition , This can cause increase in the cluster usage"
  ::= { caNotifsGroup 387 }

possibleMetadataInconsistencyNotif NOTIFICATION-TYPE
  OBJECTS { possibleMetadataInconsistencyEvent }
  STATUS current
  DESCRIPTION
    "Cohesity alert notification."
  ::= { caNotifsGroup 388 }

awsESIndexingErrorsNotif NOTIFICATION-TYPE
  OBJECTS { awsESIndexingErrorsEvent }
  STATUS current
  DESCRIPTION
    "Cohesity alert notification."
  ::= { caNotifsGroup 389 }

corruptMFTErrorNotif NOTIFICATION-TYPE
  OBJECTS { corruptMFTErrorEvent }
  STATUS current
  DESCRIPTION
    "Cohesity alert notification."
  ::= { caNotifsGroup 390 }

protectionGroupWarningNotif NOTIFICATION-TYPE
  OBJECTS { protectionGroupWarningEvent }
  STATUS current
  DESCRIPTION
    "Cohesity alert notification."
  ::= { caNotifsGroup 391 }

magnetoUnableToReachYodaNotif NOTIFICATION-TYPE
  OBJECTS { magnetoUnableToReachYodaEvent }
  STATUS current
  DESCRIPTION
    "Protection service is unable to contact indexing service"
  ::= { caNotifsGroup 392 }

secureShellEnabledNotif NOTIFICATION-TYPE
  OBJECTS { secureShellEnabledEvent }
  STATUS current
  DESCRIPTION
    "Secure shell enabled."
  ::= { caNotifsGroup 393 }

secureShellDisabledNotif NOTIFICATION-TYPE
  OBJECTS { secureShellDisabledEvent }
  STATUS current
  DESCRIPTION
    "Secure shell disabled."
  ::= { caNotifsGroup 394 }

protectionRunExpiringNotif NOTIFICATION-TYPE
  OBJECTS { protectionRunExpiringEvent }
  STATUS current
  DESCRIPTION
    "Protection Run close to expiry and having one or more failed copies."
  ::= { caNotifsGroup 395 }

vipPingFailedNotif NOTIFICATION-TYPE
  OBJECTS { vipPingFailedEvent }
  STATUS current
  DESCRIPTION
    "Cohesity alert notification."
  ::= { caNotifsGroup 396 }

oracleUnresponsiveProgressQueryNotif NOTIFICATION-TYPE
  OBJECTS { oracleUnresponsiveProgressQueryEvent }
  STATUS current
  DESCRIPTION
    "Cohesity alert notification."
  ::= { caNotifsGroup 397 }

abacServerNotReachableNotif NOTIFICATION-TYPE
  OBJECTS { abacServerNotReachableEvent }
  STATUS current
  DESCRIPTION
    "S3 ABAC server is not reachable."
  ::= { caNotifsGroup 398 }

abacServerCertExpiredNotif NOTIFICATION-TYPE
  OBJECTS { abacServerCertExpiredEvent }
  STATUS current
  DESCRIPTION
    "S3 ABAC server certificate has expired."
  ::= { caNotifsGroup 399 }

failedToChangeAuthForBackupViewNotif NOTIFICATION-TYPE
  OBJECTS { failedToChangeAuthForBackupViewEvent }
  STATUS current
  DESCRIPTION
    "Failed to set / unset service auth config for some backup views."
  ::= { caNotifsGroup 400 }

agentCertIsAboutToExpireNotif NOTIFICATION-TYPE
  OBJECTS { agentCertIsAboutToExpireEvent }
  STATUS current
  DESCRIPTION
    "Agent certificate is about to expire."
  ::= { caNotifsGroup 401 }

replicationHandshakeStuckNotif NOTIFICATION-TYPE
  OBJECTS { replicationHandshakeStuckEvent }
  STATUS current
  DESCRIPTION
    "Handshake between the local and the remote cluster is stuck for the replication."
  ::= { caNotifsGroup 402 }

highUnreclaimedGarbageAlertNotif NOTIFICATION-TYPE
  OBJECTS { highUnreclaimedGarbageAlertEvent }
  STATUS current
  DESCRIPTION
    "Critically high amount of unclaimed garbage has been detected on the cluster."
  ::= { caNotifsGroup 403 }

certificateIsAboutToExpireNotif NOTIFICATION-TYPE
  OBJECTS { certificateIsAboutToExpireEvent }
  STATUS current
  DESCRIPTION
    "Certificate is about to expire alert notification."
  ::= { caNotifsGroup 404 }

clockSkewBetweenClusterAndDCNotif NOTIFICATION-TYPE
  OBJECTS { clockSkewBetweenClusterAndDCEvent }
  STATUS current
  DESCRIPTION
    "There's a big clock skew between Cohesity cluster and Domain Controller. Will fail the authentication with this DC."
  ::= { caNotifsGroup 405 }

insecureClientDetectedNotif NOTIFICATION-TYPE
  OBJECTS { insecureClientDetectedEvent }
  STATUS current
  DESCRIPTION
    "External client not using mTSL to connect to Cohesity cluster."
  ::= { caNotifsGroup 406 }

teamsPublicChannelsIndexingAlertNotif NOTIFICATION-TYPE
  OBJECTS { teamsPublicChannelsIndexingAlertEvent }
  STATUS current
  DESCRIPTION
    "Indexing of public channels for an O365 Team is skipped as it has high number of public channels. This is an informative alert, not any failure. Please contact support team or refer to KB for details."
  ::= { caNotifsGroup 407 }

knownIssueDetectedAlertNotif NOTIFICATION-TYPE
  OBJECTS { knownIssueDetectedAlertEvent }
  STATUS current
  DESCRIPTION
    "Cohesity alert notification."
  ::= { caNotifsGroup 408 }

knownIssueDetectedCommandNotif NOTIFICATION-TYPE
  OBJECTS { knownIssueDetectedCommandEvent }
  STATUS current
  DESCRIPTION
    "Cohesity alert notification."
  ::= { caNotifsGroup 409 }

knownIssueDetectedGflagNotif NOTIFICATION-TYPE
  OBJECTS { knownIssueDetectedGflagEvent }
  STATUS current
  DESCRIPTION
    "Cohesity alert notification."
  ::= { caNotifsGroup 410 }

knownIssueDetectedPatchNotif NOTIFICATION-TYPE
  OBJECTS { knownIssueDetectedPatchEvent }
  STATUS current
  DESCRIPTION
    "Cohesity alert notification."
  ::= { caNotifsGroup 411 }

importantAwarenessCommunicationNotif NOTIFICATION-TYPE
  OBJECTS { importantAwarenessCommunicationEvent }
  STATUS current
  DESCRIPTION
    "Important Awareness Communication"
  ::= { caNotifsGroup 412 }

newPatchAvailableNotif NOTIFICATION-TYPE
  OBJECTS { newPatchAvailableEvent }
  STATUS current
  DESCRIPTION
    "A new patch for your software release is available for download"
  ::= { caNotifsGroup 413 }

knownIssueDetectedDocNotif NOTIFICATION-TYPE
  OBJECTS { knownIssueDetectedDocEvent }
  STATUS current
  DESCRIPTION
    "Cohesity alert notification."
  ::= { caNotifsGroup 414 }

knownIssueDetectedHotfixNotif NOTIFICATION-TYPE
  OBJECTS { knownIssueDetectedHotfixEvent }
  STATUS current
  DESCRIPTION
    "Cohesity alert notification."
  ::= { caNotifsGroup 415 }

highUnreachableChunksAlertNotif NOTIFICATION-TYPE
  OBJECTS { highUnreachableChunksAlertEvent }
  STATUS current
  DESCRIPTION
    "Cohesity alert notification."
  ::= { caNotifsGroup 416 }

remoteStorageRegistrationInvalidNotif NOTIFICATION-TYPE
  OBJECTS { remoteStorageRegistrationInvalidEvent }
  STATUS current
  DESCRIPTION
    "Remote storage registration information is invalid."
  ::= { caNotifsGroup 418 }

userAccountIsAboutToBeLockedNotif NOTIFICATION-TYPE
  OBJECTS { userAccountIsAboutToBeLockedEvent }
  STATUS current
  DESCRIPTION
    "User account is about to be locked."
  ::= { caNotifsGroup 419 }

cohesitySnmpTestNotif NOTIFICATION-TYPE
  OBJECTS { cohesitySnmpTestEvent }
  STATUS current
  DESCRIPTION
    "Cohesity SNMP Test Notification."
  ::= { caNotifsGroup 10000 }

-- *****************************************************************
--
-- Conformance information section
--
-- *****************************************************************

cohesityApplianceMIBCompliances  OBJECT IDENTIFIER ::= { cohesityApplianceMIBConformance 1 }

cohesityApplianceMIBGroups  OBJECT IDENTIFIER ::= { cohesityApplianceMIBConformance 2 }

-- *****************************************************************
--
-- Compliance statement section
--
-- *****************************************************************

cohesityApplianceMIBCompliance MODULE-COMPLIANCE
  STATUS       current
  DESCRIPTION "The Cohesity Appliance Compliance Statement."
  MODULE    -- this module
    MANDATORY-GROUPS {
    caObjectGroup,
    caNotificationGroup
  }
  ::= { cohesityApplianceMIBCompliances 1 }

caObjectGroup OBJECT-GROUP
  OBJECTS {
    diskNotHealthyEvent,
    nodePingFailedEvent,
    markDiskForRemovalEvent,
    upgradeFailedEvent,
    newDiskFoundEvent,
    diskSpaceLowEvent,
    timeServiceEvent,
    missingDiskEvent,
    writeLimitEvent,
    memUncorrectableEccEvent,
    watchdogTriggeredEvent,
    tempOutOfHighRangeEvent,
    tempOutOfLowRangeEvent,
    voltOutOfHighRangeEvent,
    voltOutOfLowRangeEvent,
    driveRemovedEvent,
    drivePresentEvent,
    driveFaultEvent,
    powerSupplyRemovedEvent,
    powerSupplyInsertedEvent,
    linkIsDownEvent,
    linkIsUpEvent,
    ipmiSelClearedEvent,
    nodeRebootedEvent,
    thermalTripTriggeredEvent,
    powerSupplyAcLostEvent,
    nodeChassisChangedEvent,
    raidDegradedEvent,
    diskAddedToClusterEvent,
    systemLedAmberEvent,
    cpuThrottledEvent,
    fanRemovedEvent,
    fanInsertedEvent,
    fanSpeedOutOfLowRangeEvent,
    chassisDownEvent,
    ipmiUnreachableEvent,
    ipmiNetworkConfigFailedEvent,
    ipmiUserUpdateFailedEvent,
    ipmiConfigAbsentEvent,
    ipmiEventEvent,
    storageDomainQuotaEvent,
    yodaAgentUnhealthyEvent,
    searchIndexManualMigrationNeededEvent,
    searchIndexMigrationFinishedEvent,
    searchIndexMigrationTriggeredEvent,
    searchIndexMigrationBacklogEvent,
    vMOptimizedXFSVolumeIndexingSkippedEvent,
    vMOptimizedNTFSVolumeIndexingSkippedEvent,
    aVThreatFoundEvent,
    corruptFileSystemNotIndexedEvent,
    indexingPausedEvent,
    viewQuotaEvent,
    usersExceededQuotaEvent,
    notEnoughNodesEvent,
    aVServerLicenseErrorEvent,
    internalSchedulingWarningEvent,
    cloudTierWarningEvent,
    switchCongestionEvent,
    nodeVirtualizationSupportDisabledEvent,
    sshTimeoutChangedEvent,
    bondUnhealthyEvent,
    bondSlavesSpeedInconsistentEvent,
    unexpectedInterfaceIpSettingEvent,
    scriptRunErrorEvent,
    diskIsBadEvent,
    adDomainControllersNotReachableEvent,
    upgradeStuckEvent,
    productModelIncompatibleEvent,
    directoriesExceededQuotaEvent,
    algorithmBacklogAlertEvent,
    clearStaleMountPointsTimeoutEvent,
    addNodeFailedEvent,
    directoryExceededQuotaAlertLimitEvent,
    clusterBringupErrorEvent,
    chunkFileBadStateEvent,
    tablesLargerThanExpectedEvent,
    keyRotationPolicyChangedEvent,
    potentialClusterErrorEvent,
    clusterGatewayUnReachableEvent,
    dnsServerUnReachableEvent,
    verifyVlanHostNameEvent,
    lowFaultTolerantStorageDomainEvent,
    securityPolicyDenialEvent,
    bondModeAutoMigratedEvent,
    nisDomainNotReachableEvent,
    nodeRemovedEvent,
    nodeInsertedEvent,
    inconsistentStaticRoutesEvent,
    chunkFileInconsistencyEvent,
    accessToExternalTargetFailedEvent,
    remoteReplicationBackupUserQuotaSkippedEvent,
    remoteReplicationRestoreUserQuotaSkippedEvent,
    remoteReplicationFileSkippedEvent,
    chunkFileReplicaBadStateEvent,
    remoteReplicationSetupIncompatibleEvent,
    taskProgressHungEvent,
    missingDiskFilesEvent,
    nodePoweredOffEvent,
    metadataInconsistencyAlertEvent,
    diskMarkedOfflineEvent,
    activeDirectoryNotReachableEvent,
    kernelPanicEvent,
    clusterSpaceUsageHighEvent,
    storageDomainSpaceUsageHighEvent,
    nodeFailureIsNotToleratedEvent,
    searchClusterHealthEvent,
    protectionGroupFailedEvent,
    protectedObjectFailedEvent,
    metadataServerUnreachableEvent,
    metadataUnavailableEvent,
    metadataShuffleNotProgressingEvent,
    searchIndexSizeExceedsThresholdEvent,
    searchIndexShuffleNotProgressingEvent,
    metadataCannotTolerateAnymoreFailuresEvent,
    metadataCannotAchieveConfiguredFaultToleranceFactorEvent,
    searchIndexUnavailableEvent,
    metadataCanRunOutOfSpaceUponFailureEvent,
    diskAddedToBlacklistEvent,
    diskSlotAvailableEvent,
    protectionGroupSlaViolatedEvent,
    protectionGroupcanceledBlackoutWindowEvent,
    policyFieldsDeprecatedEvent,
    protectedObjectCancelledBlackoutWindowEvent,
    protectionGroupArchivalBacklogEvent,
    archiveJobFailedEvent,
    archiveJobStuckEvent,
    restoreJobFailedEvent,
    restoreJobStuckEvent,
    protectedObjectSlaViolatedEvent,
    protectionGroupReplicationBacklogEvent,
    missingVMBackupEvent,
    vMCrackingSkippedEvent,
    vMWareMountFailureEvent,
    vMVolumeIndexingSkippedEvent,
    remoteReplicationTaskStuckEvent,
    remoteReplicationTaskFailedEvent,
    frequentProcessRestartsEvent,
    protectionGroupProgressingSlowlyEvent,
    mtuUnexpectedEvent,
    gatewayUnexpectedEvent,
    linkStatsIsNotNormalEvent,
    upgradeSucceededEvent,
    upgradeStartedEvent,
    bondingModeUnexpectedEvent,
    vLANUnexpectedEvent,
    kIntegralVolumeReachingMaxCapacityEvent,
    mediaErrorDuringRestoreEvent,
    mediaErrorDuringArchivalEvent,
    diskWithTooManyDeltaRecordsEvent,
    unresponsiveChildDeathEvent,
    encryptionKeyRotatedEvent,
    encryptionKeyCreatedEvent,
    newUpgradePackagesAvailableEvent,
    invalidStateEvent,
    metadataSizeExceedsThresholdEvent,
    keystoneNotReachableEvent,
    dataResilienceAtRiskEvent,
    diskAwaitHighEvent,
    raidInactiveEvent,
    removeNodeSuccessEvent,
    routesMigrationOnBondFailedEvent,
    serviceDownEvent,
    configureVipFailedEvent,
    ipMigrationOnBondFailedEvent,
    firewallErrorEvent,
    usbDiskFoundEvent,
    bootDiskHealthEvent,
    etcHostsFileErrorEvent,
    smallMemorySizeEvent,
    userExceededQuotaAlertLimitEvent,
    addNodeSuccessEvent,
    forcefulRemoveNodeWarningEvent,
    aVServerConnectionFailedEvent,
    adPreferredDomainControllerNotReachableEvent,
    blobJournalInconsistencyEvent,
    viewLatencyHighEvent,
    potentialMinorClusterErrorEvent,
    iceboxDedupCacheFullEvent,
    clusterServiceGflagsFoundEvent,
    virtualApplianceResourcesUnexpectedEvent,
    clusterPartitionCreateFailedEvent,
    proxyServerUnreachableEvent,
    serviceVersionsMismatchedEvent,
    firmwareIncompatibleEvent,
    nodeRebootedForYodaStuckEvent,
    protectionGroupSucceededEvent,
    unregisterExternalTargetFailedEvent,
    licenseServerUnreachableEvent,
    invalidLicenseEvent,
    unlicensedClusterEvent,
    verifyRemoteClusterConnectionEvent,
    sysSrvcErrorsEvent,
    bridgeMigrationFailedEvent,
    bridgeMigrationRevertFailedEvent,
    productModelInterfacesInconsistencyEvent,
    clusterInterfacesInconsistencyEvent,
    ntpServerUnReachableEvent,
    externalTargetNotReachableEvent,
    appInstanceUnhealthyEvent,
    indexingBacklogEvent,
    searchNodeBusyEvent,
    nonEmptyUnmountedDirectoryEvent,
    rhinoUnhealthyEvent,
    lessCPUCoreEvent,
    licenseExpiredEvent,
    licenseAboutToExpireEvent,
    biosAndBmcVersionMismatchEvent,
    unusedGflagsEvent,
    supportChannelAboutToCloseEvent,
    licenseAccountOverUseEvent,
    licenseIdentityInvalidEvent,
    kMSCertificateWillExpireEvent,
    kMSCertificateExpirationEvent,
    kMSErrorEvent,
    keyObjectCreatedEvent,
    keyObjectDestroyedEvent,
    kMSUnreachableEvent,
    diskMarkedForRemovalEvent,
    nodeMarkedForRemovalEvent,
    addNodesStartedEvent,
    diskRemovedEvent,
    sshKeyMismatchEvent,
    bMCModuleNotAvailableEvent,
    outOfMemoryRestartEvent,
    metadataInstanceHasUnrecoverableErrorEvent,
    metadataDiskRanOutOfSpaceEvent,
    licenseStatsHistoryCollectionEvent,
    dnsServerConnectionFailedEvent,
    nASVaultIsFullEvent,
    protectionGroupReplicationFailedEvent,
    diskIdMismatchEvent,
    continuousDataProtectionDisabledEvent,
    protectionPolicyDeletedEvent,
    objectBackupSlaViolatedEvent,
    objectBackupFailedEvent,
    auditLogFailureEvent,
    silicomNicFoundEvent,
    diskRemovalCancelledEvent,
    metadataMigrationsNotProgressingEvent,
    manualBackgroundSystemThrottlingAppliedEvent,
    remoteStorageUsageHighEvent,
    remoteStorageCapacityChangedEvent,
    routingDaemonDownEvent,
    remoteStorageManagementIpUnreachableEvent,
    remoteStorageFileSystemMountFailedEvent,
    remoteStorageFileSystemDeletedEvent,
    remoteStorageFileSystemUsageHighEvent,
    nfsShareNotHealthyEvent,
    scribeBackgroundOpsStallingEvent,
    eSDiskUsageExceedsThresholdEvent,
    dnsServerUnassignedEvent,
    insufficientResourcesToLaunchSysSrvPodEvent,
    userDefaultPasswordEvent,
    vMMigrationIdentifiedEvent,
    wormChangeForGroupAlertEvent,
    wormChangeForPolicyAlertEvent,
    inconsistentInterfaceGroupSpeedEvent,
    atomNodeMemoryAboveThresholdEvent,
    diskWithCorruptedPartitionTableEvent,
    remoteStorageDataIpUnreachableEvent,
    nodeTcpOrphanConnectionsExceededEvent,
    appNetworkMasterUnhealthyEvent,
    appNetworkNodeUnhealthyEvent,
    lowReplicationFactorEvent,
    duplicateIpDetectedEvent,
    powerSupplyAcRestoredEvent,
    remoteClusterNotReachableEvent,
    remoteStorageUnexpectedNfsExportRulesEvent,
    unregisteredClusterEvent,
    clusterPendingAuditReportUploadEvent,
    appNetworkResourceUnhealthyEvent,
    entityWithTooManyOpenHandlesEvent,
    viewSlowProtocolOpEvent,
    policyDatalockDurationChangedEvent,
    protectionPolicyModifiedEvent,
    protectionGroupModifiedEvent,
    protectionRunModifiedEvent,
    viewFailoverDuplicateViewUIDEvent,
    viewFailoverReplicationFailedEvent,
    viewFailoverStuckEvent,
    viewFailoverFailedEvent,
    viewFailoverStateUpdateFailedEvent,
    vaultConfigValidationFailedEvent,
    remoteReplicationTrackingViewUpdateFailedEvent,
    remoteIndexingFallbackEvent,
    archiveObjectGCFailedAlertEvent,
    highRPCLatenciesEvent,
    unexpectedIpAddressEvent,
    policyDatalockChangedEvent,
    protectionGroupDeletedEvent,
    sourceConnectivityFailureEvent,
    diskOkToRemoveEvent,
    systemServiceAppInstallationFailedEvent,
    nexusFaultIsolationRecoveryEvent,
    continuousDataProtectionAlertEvent,
    hostShellAccessExpiryEvent,
    bucketMetadataModifiedEvent,
    bucketACLUpdatedEvent,
    bucketCreatedEvent,
    bucketDeletedEvent,
    serviceGflagsChangedEvent,
    algorithmFrequentlyTimeOutAlertEvent,
    successfulFailoverOpAlertEvent,
    successfulFailbackOpAlertEvent,
    successfulTestAndDevOpAlertEvent,
    successfulPrepareFailbackOpAlertEvent,
    successfulTeardownOpAlertEvent,
    failedFailoverOpAlertEvent,
    failedFailbackOpAlertEvent,
    failedTestAndDevOpAlertEvent,
    failedPrepareFailbackOpAlertEvent,
    failedTeardownOpAlertEvent,
    ssdMediaErrorEvent,
    diskNeedFirmwareUpgradeEvent,
    metadataMovedToFlashbladeEvent,
    viewCloneMetadataBloatEvent,
    chunkFileContainerInconsistencyEvent,
    apolloIssuedActionVersionMismatchEvent,
    networkStatsIsNotNormalEvent,
    highClusterUtilizationEvent,
    createSnapshotSucceededEvent,
    nodeConnectivityFailedEvent,
    deferScheduleEvent,
    cloudDataOpFailureEvent,
    objectStorePortalInitializationFailureEvent,
    kubernetesObjectsCleanupAlertEvent,
    nodeNotPresentInKubernetesClusterEvent,
    objectDeletionRejectedEvent,
    rpmPackageVersionMismatchedEvent,
    baseOSVersionMismatchedEvent,
    createSnapshotFailedEvent,
    restoreSnapshotStartedEvent,
    restoreSnapshotSucceededEvent,
    restoreSnapshotFailedEvent,
    createSnapshotStartedEvent,
    principalWithNonViewerRoleEvent,
    azureCEHostCachingEnabledEvent,
    recentLogBeingRotatedEvent,
    repeatedlyFailingShardAlertEvent,
    backlogDuringBlackOutEvent,
    timeConsumingShardAlertEvent,
    highNonDedupToDedupPercentEvent,
    appsModeDisabledDueToSubnetClashEvent,
    oracleMountFailureEvent,
    protectionServiceNotInitializedEvent,
    fragmentActionsRepeatedlyFailingAlertEvent,
    userTuningsStuckAlertIdEvent,
    kBrickMetadataInconsistentStateEvent,
    eCConversionBackloggedEvent,
    diskSwappedEvent,
    remoteStorageConfigureFailedEvent,
    aVHighRequestQueueSizeEvent,
    aVHighResponseTimeEvent,
    orphanEntityValueVersionMismatchEvent,
    heavyFileOperationContentionEvent,
    verifyNonExistentBrickFailedEvent,
    chunkMigrationVerifyChunkInCfmFailedEvent,
    chunkMigrationVerifyBrickOwnedNDDChunksFailedEvent,
    gCStalledAlertEvent,
    upgradeCancelledEvent,
    oracleRestoreChainBreakEvent,
    nasSourceSnapshotDeletionFailedEvent,
    isilonChangelistCleanupFailedEvent,
    nodeRemovalStuckEvent,
    diskRemovalStuckEvent,
    kMSFailoverEvent,
    restoreTaskWarningEvent,
    restoreTaskFailedEvent,
    overwriteThrottlingScheduleAlertEvent,
    uIUserLockoutEvent,
    uILoginFailureEvent,
    uILoginSuccessEvent,
    inactivityUITimeoutChangedEvent,
    absoluteUITimeoutChangedEvent,
    sSHLoginSuccessEvent,
    sSHLoginFailureEvent,
    clusterServicesManuallyStoppedEvent,
    clusterServicesManuallyStartedEvent,
    cloneBackupCleanupIssuesEvent,
    tenantIndexingConfigMissingEvent,
    staleDirsFoundInYodaCloneBackupViewsEvent,
    archiveValidationFailedAlertEvent,
    remoteReplicationEncryptionKeyMismatchEvent,
    morphedGarbageThresholdExceededAlertEvent,
    switchedToSpaceModeEvent,
    imbalanceThresholdExceededAlertEvent,
    possibleMetadataInconsistencyEvent,
    awsESIndexingErrorsEvent,
    corruptMFTErrorEvent,
    protectionGroupWarningEvent,
    magnetoUnableToReachYodaEvent,
    secureShellEnabledEvent,
    secureShellDisabledEvent,
    protectionRunExpiringEvent,
    vipPingFailedEvent,
    oracleUnresponsiveProgressQueryEvent,
    abacServerNotReachableEvent,
    abacServerCertExpiredEvent,
    failedToChangeAuthForBackupViewEvent,
    agentCertIsAboutToExpireEvent,
    replicationHandshakeStuckEvent,
    highUnreclaimedGarbageAlertEvent,
    certificateIsAboutToExpireEvent,
    clockSkewBetweenClusterAndDCEvent,
    insecureClientDetectedEvent,
    teamsPublicChannelsIndexingAlertEvent,
    knownIssueDetectedAlertEvent,
    knownIssueDetectedCommandEvent,
    knownIssueDetectedGflagEvent,
    knownIssueDetectedPatchEvent,
    importantAwarenessCommunicationEvent,
    newPatchAvailableEvent,
    knownIssueDetectedDocEvent,
    knownIssueDetectedHotfixEvent,
    highUnreachableChunksAlertEvent,
    remoteStorageRegistrationInvalidEvent,
    userAccountIsAboutToBeLockedEvent,
    cohesitySnmpTestEvent
  }
  STATUS       current
  DESCRIPTION "The Cohesity Appliance Object Group."
  ::= { cohesityApplianceMIBGroups 1 }

caNotificationGroup NOTIFICATION-GROUP
  NOTIFICATIONS {
    diskNotHealthyNotif,
    nodePingFailedNotif,
    markDiskForRemovalNotif,
    upgradeFailedNotif,
    newDiskFoundNotif,
    diskSpaceLowNotif,
    timeServiceNotif,
    missingDiskNotif,
    writeLimitNotif,
    memUncorrectableEccNotif,
    watchdogTriggeredNotif,
    tempOutOfHighRangeNotif,
    tempOutOfLowRangeNotif,
    voltOutOfHighRangeNotif,
    voltOutOfLowRangeNotif,
    driveRemovedNotif,
    drivePresentNotif,
    driveFaultNotif,
    powerSupplyRemovedNotif,
    powerSupplyInsertedNotif,
    linkIsDownNotif,
    linkIsUpNotif,
    ipmiSelClearedNotif,
    nodeRebootedNotif,
    thermalTripTriggeredNotif,
    powerSupplyAcLostNotif,
    nodeChassisChangedNotif,
    raidDegradedNotif,
    diskAddedToClusterNotif,
    systemLedAmberNotif,
    cpuThrottledNotif,
    fanRemovedNotif,
    fanInsertedNotif,
    fanSpeedOutOfLowRangeNotif,
    chassisDownNotif,
    ipmiUnreachableNotif,
    ipmiNetworkConfigFailedNotif,
    ipmiUserUpdateFailedNotif,
    ipmiConfigAbsentNotif,
    ipmiEventNotif,
    storageDomainQuotaNotif,
    yodaAgentUnhealthyNotif,
    searchIndexManualMigrationNeededNotif,
    searchIndexMigrationFinishedNotif,
    searchIndexMigrationTriggeredNotif,
    searchIndexMigrationBacklogNotif,
    vMOptimizedXFSVolumeIndexingSkippedNotif,
    vMOptimizedNTFSVolumeIndexingSkippedNotif,
    aVThreatFoundNotif,
    corruptFileSystemNotIndexedNotif,
    indexingPausedNotif,
    viewQuotaNotif,
    usersExceededQuotaNotif,
    notEnoughNodesNotif,
    aVServerLicenseErrorNotif,
    internalSchedulingWarningNotif,
    cloudTierWarningNotif,
    switchCongestionNotif,
    nodeVirtualizationSupportDisabledNotif,
    sshTimeoutChangedNotif,
    bondUnhealthyNotif,
    bondSlavesSpeedInconsistentNotif,
    unexpectedInterfaceIpSettingNotif,
    scriptRunErrorNotif,
    diskIsBadNotif,
    adDomainControllersNotReachableNotif,
    upgradeStuckNotif,
    productModelIncompatibleNotif,
    directoriesExceededQuotaNotif,
    algorithmBacklogAlertNotif,
    clearStaleMountPointsTimeoutNotif,
    addNodeFailedNotif,
    directoryExceededQuotaAlertLimitNotif,
    clusterBringupErrorNotif,
    chunkFileBadStateNotif,
    tablesLargerThanExpectedNotif,
    keyRotationPolicyChangedNotif,
    potentialClusterErrorNotif,
    clusterGatewayUnReachableNotif,
    dnsServerUnReachableNotif,
    verifyVlanHostNameNotif,
    lowFaultTolerantStorageDomainNotif,
    securityPolicyDenialNotif,
    bondModeAutoMigratedNotif,
    nisDomainNotReachableNotif,
    nodeRemovedNotif,
    nodeInsertedNotif,
    inconsistentStaticRoutesNotif,
    chunkFileInconsistencyNotif,
    accessToExternalTargetFailedNotif,
    remoteReplicationBackupUserQuotaSkippedNotif,
    remoteReplicationRestoreUserQuotaSkippedNotif,
    remoteReplicationFileSkippedNotif,
    chunkFileReplicaBadStateNotif,
    remoteReplicationSetupIncompatibleNotif,
    taskProgressHungNotif,
    missingDiskFilesNotif,
    nodePoweredOffNotif,
    metadataInconsistencyAlertNotif,
    diskMarkedOfflineNotif,
    activeDirectoryNotReachableNotif,
    kernelPanicNotif,
    clusterSpaceUsageHighNotif,
    storageDomainSpaceUsageHighNotif,
    nodeFailureIsNotToleratedNotif,
    searchClusterHealthNotif,
    protectionGroupFailedNotif,
    protectedObjectFailedNotif,
    metadataServerUnreachableNotif,
    metadataUnavailableNotif,
    metadataShuffleNotProgressingNotif,
    searchIndexSizeExceedsThresholdNotif,
    searchIndexShuffleNotProgressingNotif,
    metadataCannotTolerateAnymoreFailuresNotif,
    metadataCannotAchieveConfiguredFaultToleranceFactorNotif,
    searchIndexUnavailableNotif,
    metadataCanRunOutOfSpaceUponFailureNotif,
    diskAddedToBlacklistNotif,
    diskSlotAvailableNotif,
    protectionGroupSlaViolatedNotif,
    protectionGroupcanceledBlackoutWindowNotif,
    policyFieldsDeprecatedNotif,
    protectedObjectCancelledBlackoutWindowNotif,
    protectionGroupArchivalBacklogNotif,
    archiveJobFailedNotif,
    archiveJobStuckNotif,
    restoreJobFailedNotif,
    restoreJobStuckNotif,
    protectedObjectSlaViolatedNotif,
    protectionGroupReplicationBacklogNotif,
    missingVMBackupNotif,
    vMCrackingSkippedNotif,
    vMWareMountFailureNotif,
    vMVolumeIndexingSkippedNotif,
    remoteReplicationTaskStuckNotif,
    remoteReplicationTaskFailedNotif,
    frequentProcessRestartsNotif,
    protectionGroupProgressingSlowlyNotif,
    mtuUnexpectedNotif,
    gatewayUnexpectedNotif,
    linkStatsIsNotNormalNotif,
    upgradeSucceededNotif,
    upgradeStartedNotif,
    bondingModeUnexpectedNotif,
    vLANUnexpectedNotif,
    kIntegralVolumeReachingMaxCapacityNotif,
    mediaErrorDuringRestoreNotif,
    mediaErrorDuringArchivalNotif,
    diskWithTooManyDeltaRecordsNotif,
    unresponsiveChildDeathNotif,
    encryptionKeyRotatedNotif,
    encryptionKeyCreatedNotif,
    newUpgradePackagesAvailableNotif,
    invalidStateNotif,
    metadataSizeExceedsThresholdNotif,
    keystoneNotReachableNotif,
    dataResilienceAtRiskNotif,
    diskAwaitHighNotif,
    raidInactiveNotif,
    removeNodeSuccessNotif,
    routesMigrationOnBondFailedNotif,
    serviceDownNotif,
    configureVipFailedNotif,
    ipMigrationOnBondFailedNotif,
    firewallErrorNotif,
    usbDiskFoundNotif,
    bootDiskHealthNotif,
    etcHostsFileErrorNotif,
    smallMemorySizeNotif,
    userExceededQuotaAlertLimitNotif,
    addNodeSuccessNotif,
    forcefulRemoveNodeWarningNotif,
    aVServerConnectionFailedNotif,
    adPreferredDomainControllerNotReachableNotif,
    blobJournalInconsistencyNotif,
    viewLatencyHighNotif,
    potentialMinorClusterErrorNotif,
    iceboxDedupCacheFullNotif,
    clusterServiceGflagsFoundNotif,
    virtualApplianceResourcesUnexpectedNotif,
    clusterPartitionCreateFailedNotif,
    proxyServerUnreachableNotif,
    serviceVersionsMismatchedNotif,
    firmwareIncompatibleNotif,
    nodeRebootedForYodaStuckNotif,
    protectionGroupSucceededNotif,
    unregisterExternalTargetFailedNotif,
    licenseServerUnreachableNotif,
    invalidLicenseNotif,
    unlicensedClusterNotif,
    verifyRemoteClusterConnectionNotif,
    sysSrvcErrorsNotif,
    bridgeMigrationFailedNotif,
    bridgeMigrationRevertFailedNotif,
    productModelInterfacesInconsistencyNotif,
    clusterInterfacesInconsistencyNotif,
    ntpServerUnReachableNotif,
    externalTargetNotReachableNotif,
    appInstanceUnhealthyNotif,
    indexingBacklogNotif,
    searchNodeBusyNotif,
    nonEmptyUnmountedDirectoryNotif,
    rhinoUnhealthyNotif,
    lessCPUCoreNotif,
    licenseExpiredNotif,
    licenseAboutToExpireNotif,
    biosAndBmcVersionMismatchNotif,
    unusedGflagsNotif,
    supportChannelAboutToCloseNotif,
    licenseAccountOverUseNotif,
    licenseIdentityInvalidNotif,
    kMSCertificateWillExpireNotif,
    kMSCertificateExpirationNotif,
    kMSErrorNotif,
    keyObjectCreatedNotif,
    keyObjectDestroyedNotif,
    kMSUnreachableNotif,
    diskMarkedForRemovalNotif,
    nodeMarkedForRemovalNotif,
    addNodesStartedNotif,
    diskRemovedNotif,
    sshKeyMismatchNotif,
    bMCModuleNotAvailableNotif,
    outOfMemoryRestartNotif,
    metadataInstanceHasUnrecoverableErrorNotif,
    metadataDiskRanOutOfSpaceNotif,
    licenseStatsHistoryCollectionNotif,
    dnsServerConnectionFailedNotif,
    nASVaultIsFullNotif,
    protectionGroupReplicationFailedNotif,
    diskIdMismatchNotif,
    continuousDataProtectionDisabledNotif,
    protectionPolicyDeletedNotif,
    objectBackupSlaViolatedNotif,
    objectBackupFailedNotif,
    auditLogFailureNotif,
    silicomNicFoundNotif,
    diskRemovalCancelledNotif,
    metadataMigrationsNotProgressingNotif,
    manualBackgroundSystemThrottlingAppliedNotif,
    remoteStorageUsageHighNotif,
    remoteStorageCapacityChangedNotif,
    routingDaemonDownNotif,
    remoteStorageManagementIpUnreachableNotif,
    remoteStorageFileSystemMountFailedNotif,
    remoteStorageFileSystemDeletedNotif,
    remoteStorageFileSystemUsageHighNotif,
    nfsShareNotHealthyNotif,
    scribeBackgroundOpsStallingNotif,
    eSDiskUsageExceedsThresholdNotif,
    dnsServerUnassignedNotif,
    insufficientResourcesToLaunchSysSrvPodNotif,
    userDefaultPasswordNotif,
    vMMigrationIdentifiedNotif,
    wormChangeForGroupAlertNotif,
    wormChangeForPolicyAlertNotif,
    inconsistentInterfaceGroupSpeedNotif,
    atomNodeMemoryAboveThresholdNotif,
    diskWithCorruptedPartitionTableNotif,
    remoteStorageDataIpUnreachableNotif,
    nodeTcpOrphanConnectionsExceededNotif,
    appNetworkMasterUnhealthyNotif,
    appNetworkNodeUnhealthyNotif,
    lowReplicationFactorNotif,
    duplicateIpDetectedNotif,
    powerSupplyAcRestoredNotif,
    remoteClusterNotReachableNotif,
    remoteStorageUnexpectedNfsExportRulesNotif,
    unregisteredClusterNotif,
    clusterPendingAuditReportUploadNotif,
    appNetworkResourceUnhealthyNotif,
    entityWithTooManyOpenHandlesNotif,
    viewSlowProtocolOpNotif,
    policyDatalockDurationChangedNotif,
    protectionPolicyModifiedNotif,
    protectionGroupModifiedNotif,
    protectionRunModifiedNotif,
    viewFailoverDuplicateViewUIDNotif,
    viewFailoverReplicationFailedNotif,
    viewFailoverStuckNotif,
    viewFailoverFailedNotif,
    viewFailoverStateUpdateFailedNotif,
    vaultConfigValidationFailedNotif,
    remoteReplicationTrackingViewUpdateFailedNotif,
    remoteIndexingFallbackNotif,
    archiveObjectGCFailedAlertNotif,
    highRPCLatenciesNotif,
    unexpectedIpAddressNotif,
    policyDatalockChangedNotif,
    protectionGroupDeletedNotif,
    sourceConnectivityFailureNotif,
    diskOkToRemoveNotif,
    systemServiceAppInstallationFailedNotif,
    nexusFaultIsolationRecoveryNotif,
    continuousDataProtectionAlertNotif,
    hostShellAccessExpiryNotif,
    bucketMetadataModifiedNotif,
    bucketACLUpdatedNotif,
    bucketCreatedNotif,
    bucketDeletedNotif,
    serviceGflagsChangedNotif,
    algorithmFrequentlyTimeOutAlertNotif,
    successfulFailoverOpAlertNotif,
    successfulFailbackOpAlertNotif,
    successfulTestAndDevOpAlertNotif,
    successfulPrepareFailbackOpAlertNotif,
    successfulTeardownOpAlertNotif,
    failedFailoverOpAlertNotif,
    failedFailbackOpAlertNotif,
    failedTestAndDevOpAlertNotif,
    failedPrepareFailbackOpAlertNotif,
    failedTeardownOpAlertNotif,
    ssdMediaErrorNotif,
    diskNeedFirmwareUpgradeNotif,
    metadataMovedToFlashbladeNotif,
    viewCloneMetadataBloatNotif,
    chunkFileContainerInconsistencyNotif,
    apolloIssuedActionVersionMismatchNotif,
    networkStatsIsNotNormalNotif,
    highClusterUtilizationNotif,
    createSnapshotSucceededNotif,
    nodeConnectivityFailedNotif,
    deferScheduleNotif,
    cloudDataOpFailureNotif,
    objectStorePortalInitializationFailureNotif,
    kubernetesObjectsCleanupAlertNotif,
    nodeNotPresentInKubernetesClusterNotif,
    objectDeletionRejectedNotif,
    rpmPackageVersionMismatchedNotif,
    baseOSVersionMismatchedNotif,
    createSnapshotFailedNotif,
    restoreSnapshotStartedNotif,
    restoreSnapshotSucceededNotif,
    restoreSnapshotFailedNotif,
    createSnapshotStartedNotif,
    principalWithNonViewerRoleNotif,
    azureCEHostCachingEnabledNotif,
    recentLogBeingRotatedNotif,
    repeatedlyFailingShardAlertNotif,
    backlogDuringBlackOutNotif,
    timeConsumingShardAlertNotif,
    highNonDedupToDedupPercentNotif,
    appsModeDisabledDueToSubnetClashNotif,
    oracleMountFailureNotif,
    protectionServiceNotInitializedNotif,
    fragmentActionsRepeatedlyFailingAlertNotif,
    userTuningsStuckAlertIdNotif,
    kBrickMetadataInconsistentStateNotif,
    eCConversionBackloggedNotif,
    diskSwappedNotif,
    remoteStorageConfigureFailedNotif,
    aVHighRequestQueueSizeNotif,
    aVHighResponseTimeNotif,
    orphanEntityValueVersionMismatchNotif,
    heavyFileOperationContentionNotif,
    verifyNonExistentBrickFailedNotif,
    chunkMigrationVerifyChunkInCfmFailedNotif,
    chunkMigrationVerifyBrickOwnedNDDChunksFailedNotif,
    gCStalledAlertNotif,
    upgradeCancelledNotif,
    oracleRestoreChainBreakNotif,
    nasSourceSnapshotDeletionFailedNotif,
    isilonChangelistCleanupFailedNotif,
    nodeRemovalStuckNotif,
    diskRemovalStuckNotif,
    kMSFailoverNotif,
    restoreTaskWarningNotif,
    restoreTaskFailedNotif,
    overwriteThrottlingScheduleAlertNotif,
    uIUserLockoutNotif,
    uILoginFailureNotif,
    uILoginSuccessNotif,
    inactivityUITimeoutChangedNotif,
    absoluteUITimeoutChangedNotif,
    sSHLoginSuccessNotif,
    sSHLoginFailureNotif,
    clusterServicesManuallyStoppedNotif,
    clusterServicesManuallyStartedNotif,
    cloneBackupCleanupIssuesNotif,
    tenantIndexingConfigMissingNotif,
    staleDirsFoundInYodaCloneBackupViewsNotif,
    archiveValidationFailedAlertNotif,
    remoteReplicationEncryptionKeyMismatchNotif,
    morphedGarbageThresholdExceededAlertNotif,
    switchedToSpaceModeNotif,
    imbalanceThresholdExceededAlertNotif,
    possibleMetadataInconsistencyNotif,
    awsESIndexingErrorsNotif,
    corruptMFTErrorNotif,
    protectionGroupWarningNotif,
    magnetoUnableToReachYodaNotif,
    secureShellEnabledNotif,
    secureShellDisabledNotif,
    protectionRunExpiringNotif,
    vipPingFailedNotif,
    oracleUnresponsiveProgressQueryNotif,
    abacServerNotReachableNotif,
    abacServerCertExpiredNotif,
    failedToChangeAuthForBackupViewNotif,
    agentCertIsAboutToExpireNotif,
    replicationHandshakeStuckNotif,
    highUnreclaimedGarbageAlertNotif,
    certificateIsAboutToExpireNotif,
    clockSkewBetweenClusterAndDCNotif,
    insecureClientDetectedNotif,
    teamsPublicChannelsIndexingAlertNotif,
    knownIssueDetectedAlertNotif,
    knownIssueDetectedCommandNotif,
    knownIssueDetectedGflagNotif,
    knownIssueDetectedPatchNotif,
    importantAwarenessCommunicationNotif,
    newPatchAvailableNotif,
    knownIssueDetectedDocNotif,
    knownIssueDetectedHotfixNotif,
    highUnreachableChunksAlertNotif,
    remoteStorageRegistrationInvalidNotif,
    userAccountIsAboutToBeLockedNotif,
    cohesitySnmpTestNotif
  }
  STATUS       current
  DESCRIPTION "The Cohesity Appliance Notification Group."
  ::= { cohesityApplianceMIBGroups 2 }


END
