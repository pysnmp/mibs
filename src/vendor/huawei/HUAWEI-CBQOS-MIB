-- =================================================================
-- Copyright (C) 2017 by  HUAWEI TECHNOLOGIES. All rights reserved
-- 
-- Description: This mib file is used for management of huawei Class Based
--              QoS information.
-- Reference:
-- Version:     V2.30
-- History:
--              V1.0 tianli,2004.4.10,publish
--              V1.1 lizhiyong, 2004-9-14
--                  modify the hyphens which is not allowed used in SMIv2
--              v1.2
--                  changed by yangjianjun  change description of hwCBQoSMatchRuleIntValue1 and hwCBQoSMatchRuleIntValue2
--                  changed by wanghao      add an object hwCBQoSQueueCbsRatio
--                  changed by peigangqiang for LR, NestPolicy, IPV6 QoS
--              v1.3
--                  modified by chengang
--                  modified by zhangwenwu
--                  modified by hezhifeng
--                  modified by wanglili
--              v1.4
--                  modified by zhangwenwu 2005-11-17
--              v1.5
--                  modified by dongling 2008-07-12
--              v2.13
--                  modified by zhoucongya 2014-02-19
--              v2.14
--                  modified by zhangliang 2014-05-27
--              v2.15
--                  modified by caoyanping 2015-04-21
--              v2.16
--                  modified by yanruiqing 2015-09-01
--              v2.17
--                  modified by liuxiaoyan 2015-09-17
--              v2.18
--                  modified by liuxiaoyan 2016-05-13
--              v2.22
--                  modified by liye 2016-06-03
--              v2.23
--                  modified by wangcheng 2016-06-30
--              v2.24
--                  modified by shanruitang 2016-07-05
--              v2.25
--                  modified by yanruiqing 2016-08-22
--              v2.26
--                  modified by zhangyong 2016-10-19
--              v2.27
--                  modified by wangcheng 2016-11-30
--              v2.29
--                  modified by chenlong  2017-1-23
--              v2.30
--                  modified by chenlong  2017-1-23

-- ==========================================================================

    HUAWEI-CBQOS-MIB DEFINITIONS ::= BEGIN
 
        IMPORTS
            hwDatacomm            
                FROM HUAWEI-MIB
            EnabledStatus            
                FROM P-BRIDGE-MIB                        
            ifIndex            
                FROM RFC1213-MIB            
            OBJECT-GROUP, MODULE-COMPLIANCE, NOTIFICATION-GROUP         
                FROM SNMPv2-CONF            
            IpAddress, Integer32, Unsigned32, Counter64, OBJECT-TYPE, MODULE-IDENTITY, NOTIFICATION-TYPE            
                FROM SNMPv2-SMI
            InterfaceIndex    
                FROM IF-MIB            
            RowStatus, TEXTUAL-CONVENTION            
                FROM SNMPv2-TC;
    
    
        hwCBQoSMIB MODULE-IDENTITY 
            LAST-UPDATED "201701231931Z"
            ORGANIZATION 
                "Huawei Technologies Co.,Ltd."
            CONTACT-INFO 
"Huawei Industrial Base
  Bantian, Longgang
   Shenzhen 518129
   People's Republic of China
   Website: http://www.huawei.com
   Email: support@huawei.com
 "
            DESCRIPTION 
                "The HUAWEI-CBQOS-MIB contains objects to
                Manage configuration and Monitor running state
                for Class Based QoS feature.                    
        
        "
            REVISION "201701231931Z"
               DESCRIPTION
                  "MOD HwCBQoSMultiPolicyStatisticsEntry HwCBQoSMultiPolicyStatisticsClassifierEntry"

            REVISION "201612141025Z"
               DESCRIPTION
                  "MOD  hwCBQoSCarStatisticsTable hwCBQoSCarExceededByteRate"

            REVISION "201611301025Z"
               DESCRIPTION
                  "Add hwCBQoSGlobalApplyMultiPolicyTable"

            REVISION "201607051025Z"
               DESCRIPTION
                 "hwCBQoSRedirectCfgInfoTable hwCBQoSWredType"
                         
            REVISION "201606301025Z"
               DESCRIPTION
                 "MOD hwCBQoSMatchRuleType"

            REVISION "201606031025Z"
               DESCRIPTION
                 "ADD hwCBQoSUpdateUserQueueResourceNotEnoughAlarmTable hwCBQoSSetUserQueueResourceNotEnoughAlarmTable"

            REVISION "201605131719Z"
               DESCRIPTION
                 "ADD hwCBQoSSubPolicyClassName"

            REVISION "201604141737Z"
               DESCRIPTION
                 "ADD hwCBQoSGlobalCarStatisticsTable hwCBQoSGlobalPolicyStatisticsTable hwCBQoSGlobalClassifierStatisticsTable"

            REVISION "201512031737Z"
               DESCRIPTION
                 "hwCBQoSPolicyStatClassifierName"

            REVISION "201512021737Z"
               DESCRIPTION
                 "hwCBQoSPolicyStatClassifierName"

            REVISION "201509011737Z"
               DESCRIPTION
                 "MOD hwCBQoSClassifierCfgInfoEntry hwCBQoSBehaviorCfgInfoEntry hwCBQoSCarCfgInfoEntry NODE"

            REVISION "201402191737Z"
               DESCRIPTION
                  "ADD hwCBQoSPolicyStatSubPolicyClassifierRunInfoTable "

            REVISION "201307201600Z"
               DESCRIPTION
                  "ADD hwCBQoSIfApplyMultiPolicyTable  hwCBQoSVlanApplyMultiPolicyTable  hwCBQoSMultiPolicyStatisticsTable  hwCBQoSMultiPolicyStatisticsClassifierTable"
   
            REVISION "201306041600Z"
               DESCRIPTION
                  "MOD hwCBQoSPolicyClassifierIndex NODE"
     
            REVISION "201402191737Z"
               DESCRIPTION
                 "MOD hwCBQoSClassifierName hwCBQoSClassifierName hwCBQoSBehaviorName hwCBQoSPolicyName hwCBQoSPolicyClassClassifierName hwCBQoSPolicyClassBehaviorName hwCBQoSIfApplyPolicyName hwCBQoSAtmPvcApplyPolicyName   hwCBQoSIfVlanApplyPolicyName hwCBQoSVlanApplyPolicyName hwCBQoSTrapPolicyName hwCBQoSQueryPolicyName hwCBQoSQueryClassifierName NODE"  
          
            REVISION "201503281808Z"
               DESCRIPTION
                  "MOD HwCBQoSMatchRuleCfgInfoEntry NODE" 
                  
            REVISION "201509171808Z"
               DESCRIPTION
                  "MOD hwCBQoSIfApplyPolicyLinkLayer mpls-layer"
		  
            REVISION "201607051025Z"
               DESCRIPTION
                  "MOD  hwCBQoSGlobalCarStatisticsTable INDEX"
            
                        REVISION "201607051025Z"
               DESCRIPTION
                  "MOD  hwCBQoSPolicyCfgInfoTable hwCBQoSPolicyShareFlag"
            REVISION "201701231931Z"
               DESCRIPTION
                  "MOD  hwCBQoSBehaviorCfgInfoTable  hwCBQoSClassifierCfgInfoTable    hwCBQoSCarCfgInfoTable  hwCBQoSCarCir  hwCBQoSCarCbs  hwCBQoSCarPir   hwCBQoSCarPbs  hwCBQoSRemarkCfgInfoTable  hwCBQoSServiceClassCfgInfoTable  hwCBQoSPolicyCfgInfoTable   hwCBQoSPolicyClassCfgInfoTable  hwCBQoSIfApplyPolicyTable  hwCBQoSIfVlanApplyPolicyTable  hwCBQoSCarStatisticsTable  hwCBQoSPolicyStatisticsTable  hwCBQoSClassifierStatisticsTable  hwCBQoSPolicyStatisticsClassifierTable  hwCBQoSGlobalCarStatisticsTable  hwCBQoSGlobalPolicyStatisticsTable  hwCBQoSGlobalClassifierStatisticsTable  OBJECT-TYPE "	
    	  
               ::= { hwQoS 1 }
--
-- Textual conventions
--
    
--  1.3.6.1.4.1.2011.5.25.32.1
-- April 10, 2004 at 00:00 GMT
-- 
-- type definitions
-- 
-- MatchRuleType
        MatchRuleType ::= TEXTUAL-CONVENTION
            STATUS current
            DESCRIPTION 
                "Type of Match Rule. "
            SYNTAX INTEGER
                {
                any(1),
                ipv4Acl(2),
                rtpPort(3),
                protocol(4),
                ipPrec(5),
                dscp(6),
                vlan8021p(7),
                mplsExp(8),
                sourceMac(9),
                destinationMac(10),
                classifier(11),
                inboundInterface(12),
                macGroup(13),
                ipv6Acl(14),
                qosLocalId(15),
                frDe(16),
                atmClp(17),
                ipv6Dscp(18),
                ipv6NextHeader(19),
                ipv6Any(20),
                ipv6DstIp(21),
                ipv6SrcIp(22),
                ruleString(23),
                vlanId(24),
                outboundInterface(25),
                l2Protocol(26),
                l2Acl(27),
                tcpFlag(28),
                cvlanId(29),
                doubleTag(30),
                sourceQosLocalId(31),
                cvlan8021p(32),
                discard(33),
                dlci(34),
                app-protocol(35),
                protocol-group(36),
                vlanid-cvlanid(37),
                tagged-vxlan(38),
                untagged-vxlan(39),
                transit-tagged-vxlan(40),
                transit-untagged-vxlan(41)
                }

-- CarAction
        CarAction ::= TEXTUAL-CONVENTION
            STATUS current
            DESCRIPTION 
                "The actions taken when packets conforming or exceeding the configured
                CIR:
                    pass (1),
                    discard (2),
                    remark IP Precedence (3),
                    remark DSCP(4),
                    remark Mpls Exp(5),
                    remark (6),
                    remark 8021p(7)
                "
            SYNTAX INTEGER
                {
                pass(1),
                discard(2),
                remarkIpPrec(3),
                remarkDscp(4),
                remarkMplsExp(5),
                remark(6),
                remark8021p(7)
                }

-- RemarkType
        RemarkType ::= TEXTUAL-CONVENTION
            STATUS current
            DESCRIPTION 
                "IP-Prec(1)
                DSCP(2)
                MPLS-EXP(3)
                VLAN-8021p(4)
                ATM-CLP(5)
                FR-DE(6)
                QoS-Local-ID(7)
                IPV6-DSCP(8)
                Local-Prec(9)
                destination-mac(10)
                VLAN-ID(11)     
                Vlan-Protocol(12)
                "
            SYNTAX INTEGER
                {
                ipPrec(1),
                dscp(2),
                mplsExp(3),
                vlan8021p(4),
                atmClp(5),
                frDe(6),
                qosLocalId(7),
                ipv6Dscp(8),
                localPrec(9),
                destinationMac(10),
                vlanId(11),
                vlanProtocol(12)
                }

-- QueueType
        CBQueueType ::= TEXTUAL-CONVENTION
            STATUS current
            DESCRIPTION 
                "Queueing Type:
                EF: (1)
                AF: (2)
                WFQ: (3)
                LLQ: (4)
                "
            SYNTAX INTEGER
                {
                ef(1),
                af(2),
                wfq(3),
                llq(4)
                }

-- QueueBandwidthUnit
        QueueBandwidthUnit ::= TEXTUAL-CONVENTION
            STATUS current
            DESCRIPTION 
                "Bandwidth Unit:
                Absolute, Unit Kbps (1)
                Percent, Unit % (2)
                "
            SYNTAX INTEGER
                {
                unavailable(-1),
                absoluteUnitKbps(1),
                percentUnit(2)
                }

-- WredType
        WredType ::= TEXTUAL-CONVENTION
            STATUS current
            DESCRIPTION 
                "IP-Prec Based (1)
                DSCP Based (2)
                "
            SYNTAX INTEGER
                {
                ipPrecbased(1),
                dscpbased(2)
                }

-- SamplingType
        SamplingType ::= TEXTUAL-CONVENTION
            STATUS current
            DESCRIPTION 
                "Fix-packets(1)
                Fix-time(2)
                Random-packets(3)
                Random-time(4)
                "
            SYNTAX INTEGER
                {
                fixPackets(1),
                fixTime(2),
                randomPackets(3),
                randomTime(4)
                }

-- LrCirUnit
        LrCirUnit ::= TEXTUAL-CONVENTION
            STATUS current
            DESCRIPTION 
                "CIR Unit:
                Absolute, Unit bps (1)
                Percent, Unit % (2)
                "
            SYNTAX INTEGER
                {
                absoluteUnitBps(1),
                percentUnit(2)
                }

-- RedirectType
        RedirectType ::= TEXTUAL-CONVENTION
            STATUS current
            DESCRIPTION 
                "Cp(1)
                Ip-nexthop(2)
                Lsp-label(3)
                Ipv6-cp(4)
                Ipv6-nexthop(5)
                Lsp-path(6)
                "
            SYNTAX INTEGER
                {
                cp(1),
                ipNexthop(2),
                lspLabel(3),
                ipv6Cp(4),
                ipv6Nexthop(5),
                lspPath(6)
                }

-- RedirectCtrlType
        RedirectCtrlType ::= TEXTUAL-CONVENTION
            STATUS current
            DESCRIPTION 
                "Strict(1)
                Loose(2)"
            SYNTAX INTEGER
                {
                strict(1),
                loose(2)
                }

-- UrpfCtrlType
        UrpfCtrlType ::= TEXTUAL-CONVENTION
            STATUS current
            DESCRIPTION 
                "Strict(1)
                Loose(2)"
            SYNTAX INTEGER
                {
                strict(1),
                loose(2)
                }

-- Direction
        DirectionType ::= TEXTUAL-CONVENTION
            STATUS current
            DESCRIPTION 
                "The Direction Policy apply on."
            SYNTAX INTEGER
                {
                inbound(1),
                outbound(2)
                }

-- COS Type
        CosType ::= TEXTUAL-CONVENTION
            STATUS current
            DESCRIPTION 
                "CS7(8)
                CS6(7)
                EF(6)
                AF4(5)
                AF3(4)
                AF2(3)
                AF1(2)
                BE(1)"
            SYNTAX INTEGER
                {
                be(1),
                af1(2),
                af2(3),
                af3(4),
                af4(5),
                ef(6),
                cs6(7),
                cs7(8)
                }

-- PolicyApplyType
        PolicyApplyType ::= TEXTUAL-CONVENTION
            STATUS current
            DESCRIPTION 
                "UCL(0)
                ACL(1)
                ALL(2)"
            SYNTAX INTEGER
                {
                ucl(0),
                acl(1),
                all(2)
                } 
--
-- Node definitions
--
    
-- end of type definitions
-- 
-- 
-- Node definitions
-- 
-- 1.3.6.1.4.1.2011.5.25.32
        hwQoS OBJECT IDENTIFIER ::= { hwDatacomm 32 }

        
--  1.3.6.1.4.1.2011.5.25.32.1.1
        hwCBQoSObjects OBJECT IDENTIFIER ::= { hwCBQoSMIB 1 }

        
-- hwCBQoSClassifierObjects
        hwCBQoSClassifierObjects OBJECT IDENTIFIER ::= { hwCBQoSObjects 1 }

        
--  Traffic Classifier Next Index
        hwCBQoSClassifierIndexNext OBJECT-TYPE
            SYNTAX Integer32
            MAX-ACCESS read-only
            STATUS current
            DESCRIPTION
                "The value of this object identifies the index of the next available traffic classifier.
                The index defined when the user creates a traffic class must be the same as the value of hwCBQoSClassifierIndexNext; otherwise, the traffic class cannot be created."
            ::= { hwCBQoSClassifierObjects 1 }

        
--  Traffic Classifier
        hwCBQoSClassifierCfgInfoTable OBJECT-TYPE
            SYNTAX SEQUENCE OF HwCBQoSClassifierCfgInfoEntry
            MAX-ACCESS not-accessible
            STATUS current
            DESCRIPTION
                "This table is used to configure the traffic classification. Traffic classes are categorized into system-defined classes and user-defined classes. The system-defined classes cannot be created, modified, or deleted."
            ::= { hwCBQoSClassifierObjects 2 }

        
        hwCBQoSClassifierCfgInfoEntry OBJECT-TYPE
            SYNTAX HwCBQoSClassifierCfgInfoEntry
            MAX-ACCESS not-accessible
            STATUS current
            DESCRIPTION
                "  hwCBQoSClassifierCfgInfoEntry ."
            INDEX { hwCBQoSClassifierIndex }
            ::= { hwCBQoSClassifierCfgInfoTable 1 }

        
        HwCBQoSClassifierCfgInfoEntry ::=
            SEQUENCE { 
                hwCBQoSClassifierIndex
                    Integer32,
                hwCBQoSClassifierName
                    OCTET STRING,
                hwCBQoSClassifierRuleCount
                    Integer32,
                hwCBQoSClassifierOperator
                    INTEGER,
                hwCBQoSClassifierLayer
                    INTEGER,
                hwCBQoSClassifierRowStatus
                    RowStatus
             }

        hwCBQoSClassifierIndex OBJECT-TYPE
            SYNTAX Integer32
            MAX-ACCESS read-only
            STATUS current
            DESCRIPTION
                "The value of this object identifies the index of the traffic classifier.
                 The value ranges from 0 to 65535.
                 This object has no default value."
            ::= { hwCBQoSClassifierCfgInfoEntry 1 }

        
        hwCBQoSClassifierName OBJECT-TYPE
            SYNTAX OCTET STRING (SIZE (1..64))
            MAX-ACCESS read-create
            STATUS current
            DESCRIPTION
                "This object indicates the name of the traffic classifier.
The value of this object is a string of 1 to 64 visible ASCII characters.
This object has no default value.
No space can exist between characters in the string. The initial space and end space are ignored."
            ::= { hwCBQoSClassifierCfgInfoEntry 2 }

        
        hwCBQoSClassifierRuleCount OBJECT-TYPE
            SYNTAX Integer32
            MAX-ACCESS read-only
            STATUS current
            DESCRIPTION
                "The value of this object identifies the number of the matching rules for the traffic classifier.
The value ranges from 0 to 16.
This object has no default value."
            ::= { hwCBQoSClassifierCfgInfoEntry 3 }

        
        hwCBQoSClassifierOperator OBJECT-TYPE
            SYNTAX INTEGER
                {
                and(1),
                or(2)
                }
            MAX-ACCESS read-create
            STATUS current
            DESCRIPTION
                "The value of this object identifies the relationship between matching rules.
The value of this object can be AND(1) or OR(2).
The default value is OR(2)."
            ::= { hwCBQoSClassifierCfgInfoEntry 4 }

        
        hwCBQoSClassifierLayer OBJECT-TYPE
            SYNTAX INTEGER
                {
                unavailable(-1),
                l2(1),
                l3(2),
                both(3)
                }
            MAX-ACCESS read-create
            STATUS current
            DESCRIPTION
                "Configuration layer of traffic classifier.
                Only hardware QoS support it.
                -1(unavailable) is returned only when getting value from software QoS.
                -1(unavailable) can't be set."
            DEFVAL { l3 }
            ::= { hwCBQoSClassifierCfgInfoEntry 5 }

        
        hwCBQoSClassifierRowStatus OBJECT-TYPE
            SYNTAX RowStatus
            MAX-ACCESS read-create
            STATUS current
            DESCRIPTION
                "This object indicates the row status.
The value of this object can be Active(1), CreateAndGo(4), or Destroy(6).
This object has no default value."
            ::= { hwCBQoSClassifierCfgInfoEntry 6 }

        
--  Match rule
        hwCBQoSMatchRuleCfgInfoTable OBJECT-TYPE
            SYNTAX SEQUENCE OF HwCBQoSMatchRuleCfgInfoEntry
            MAX-ACCESS not-accessible
            STATUS current
            DESCRIPTION
                "A table of Match Rule configuration information."
            ::= { hwCBQoSClassifierObjects 3 }

        
        hwCBQoSMatchRuleCfgInfoEntry OBJECT-TYPE
            SYNTAX HwCBQoSMatchRuleCfgInfoEntry
            MAX-ACCESS not-accessible
            STATUS current
            DESCRIPTION
                "Match Rule Configuration Information Entry."
            INDEX { hwCBQoSClassifierIndex, hwCBQoSMatchRuleIndex, hwCBQoSMatchVlanBeginId }
            ::= { hwCBQoSMatchRuleCfgInfoTable 1 }

        
        HwCBQoSMatchRuleCfgInfoEntry ::=
            SEQUENCE { 
                hwCBQoSMatchRuleIndex
                    Integer32,
                hwCBQoSMatchRuleIfNot
                    INTEGER,
                hwCBQoSMatchRuleType
                    MatchRuleType,
                hwCBQoSMatchRuleStringValue
                    OCTET STRING,
                hwCBQoSMatchRuleIntValue1
                    Unsigned32,
                hwCBQoSMatchRuleIntValue2
                    Unsigned32,
                hwCBQoSMatchRuleRowStatus
                    RowStatus,
                hwCBQoSMatchMacMask
                    OCTET STRING,
                hwCBQoSMatchVlanBeginId
                    Unsigned32,
                hwCBQoSMatchVlanEndId
                    Unsigned32,
				hwCBQoSMatchInnerSrcIp
					IpAddress,
				hwCBQoSMatchInnerSrcIpMask
					Unsigned32,
				hwCBQoSMatchInnerDstIp
					IpAddress,
				hwCBQoSMatchInnerDstIpMask
					Unsigned32,
				hwCBQoSMatchInnerSrcPort
					Unsigned32,
				hwCBQoSMatchInnerDstPort
					Unsigned32,
				hwCBQoSMatchInnerProtocol
					Unsigned32,
				hwCBQoSMatchVxlanVni
					Unsigned32
             }

        hwCBQoSMatchRuleIndex OBJECT-TYPE
            SYNTAX Integer32
            MAX-ACCESS read-only
            STATUS current
            DESCRIPTION
                "The value of this object identifies the rule index.
The value ranges from 0 to 15.
This object has no default value."
            ::= { hwCBQoSMatchRuleCfgInfoEntry 1 }

        
        hwCBQoSMatchRuleIfNot OBJECT-TYPE
            SYNTAX INTEGER
                {
                match(1),
                notMatch(2)
                }
            MAX-ACCESS read-create
            STATUS current
            DESCRIPTION
                "The value of this object identifies the if-match rule is a Match or NotMatch statement.
The value of this object can be match(1) or match-not(2)."
            DEFVAL { match }
            ::= { hwCBQoSMatchRuleCfgInfoEntry 2 }

        
        hwCBQoSMatchRuleType OBJECT-TYPE
            SYNTAX MatchRuleType
            MAX-ACCESS read-create
            STATUS current
            DESCRIPTION
                "The value of this object identifies the rule type.
                The value of this object can be any of the following: 
                any(1)
                ipv4-acl(2)
                rtp-port(3)
                protocol(4)
                ip-prec(5)
                dscp(6)
                vlan-8021p(7)
                mpls-exp(8)
                source-mac(9)
                destination-mac(10)
                classifier(11)
                inbound-interface(12)
                mac-group(13)
                ipv6-acl(14)
                qos-local-id(15)
                fr-de(16)
                atm-clp(17)
                ipv6-dscp(18)
                ipv6-next-header(19)
                ipv6-any(20)
                ipv6-dst-ip(21)
                ipv6-src-ip(22)
                rule-string(23)
                vlan-id(24)
                outbound-interface(25)
                l2-protocol(26)
                l2Acl(27),
                tcpFlag(28),
                cvlanId(29),
                doubleTag(30),
                sourceQosLocalId(31),
                cvlan8021p(32),
                discard(33),
                dlci(34),
                app-protocol(35),
                protocol-group(36),
                vlanid-cvlanid(37),
                tagged-vxlan(38),
                untagged-vxlan(39),
                transit-tagged-vxlan(40),
                transit-untagged-vxlan(41)
                This object has no default value.
                "
            ::= { hwCBQoSMatchRuleCfgInfoEntry 3 }

        
        hwCBQoSMatchRuleStringValue OBJECT-TYPE
            SYNTAX OCTET STRING (SIZE (0..255))
            MAX-ACCESS read-create
            STATUS current
            DESCRIPTION
                "This object indicates the rule contents. The value range and the default value of the object vary with hwCBQoSMatchRuleType.
When the supported types are Source-MAC(9) and Destination-MAC(10), 
the value of this object can be a string of six ASCII characters, 
which represents a MAC address. For example, abcdef indicates the MAC address 6162-6364-6566.
When the supported types are ipv6-dst-ip(21) and ipv6-src-ip(22), 
the value of this object is a string of 16 ASCII characters, 
which represents an IPv6 address. For example, 1111111111111111 indicates an IPv6 address 3131-3131-3131-3131-3131-3131-3131-3131.
This object has no default value.
                "
            ::= { hwCBQoSMatchRuleCfgInfoEntry 4 }

        
        hwCBQoSMatchRuleIntValue1 OBJECT-TYPE
            SYNTAX Unsigned32
            MAX-ACCESS read-create
            STATUS current
            DESCRIPTION
                "This object indicates the rule contents. The value range and the default value of the object vary with hwCBQoSMatchRuleType.
When the supported type is ipv4-acl(2), the value of this object ranges from 2000 to 4099.
When the type is ip-prec(5), the value of this object ranges from 2^1 to 2^7, respectively representing the IP precedence from 0 to 7.
When the supported types are dscp(6) and ipv6-dscp(18), the value ranges from 2^1 to 2^32, respectively representing the DSCP value ranging from 32 to 63.
When the type is ipv6-acl(14), the value of this object ranges from 2000 to 3999.
When the type is ipv6-dscp(18), the value of this object ranges from 0 to 63.
When the type is Ipv6-next-header(19), the value ranges from 0 to 255.
When the type is tcp-flag(27), the value ranges from 0 to 63.
When the types are ipv6-dst-ip(21) and ipv6-src-ip(22), the value ranges from 0 to 128.
This object has no default value.
                "
            ::= { hwCBQoSMatchRuleCfgInfoEntry 5 }

        
        hwCBQoSMatchRuleIntValue2 OBJECT-TYPE
            SYNTAX Unsigned32
            MAX-ACCESS read-create
            STATUS current
            DESCRIPTION
                "This object indicates the rule contents. The value range and the default value of the object vary with hwCBQoSMatchRuleType.
When the supported type is dscp(6), the value ranges from 2^1 to 2^32, respectively representing the DSCP value ranging from 0 to 31.
This object has no default value.
                 "
            ::= { hwCBQoSMatchRuleCfgInfoEntry 6 }

        
        hwCBQoSMatchRuleRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSMatchRuleCfgInfoEntry 7 }

        
        hwCBQoSMatchMacMask OBJECT-TYPE
            SYNTAX OCTET STRING (SIZE (0..6))
            MAX-ACCESS read-create
            STATUS current
            DESCRIPTION
                "Value of Match Rule.
                Source-MAC(9): SIZE (0..6) HHHHHH  for example: ffff00 means the match rule is 'if-match source-mac XX-XX-XX ff-ff-00'
                Destination-MAC(10): SIZE (0..6) HHHHHH for example: ffff00 means the match rule is 'if-match destination-mac XX-XX-XX ff-ff-00'
                default:0XFFFFFF
                "
            ::= { hwCBQoSMatchRuleCfgInfoEntry 8 }     
            
        hwCBQoSMatchVlanBeginId OBJECT-TYPE
            SYNTAX Unsigned32   
            MAX-ACCESS not-accessible
            STATUS current
            DESCRIPTION
                "Start vlan ID."
            ::= { hwCBQoSMatchRuleCfgInfoEntry 9 }      
            
        hwCBQoSMatchVlanEndId OBJECT-TYPE
            SYNTAX Unsigned32 
            MAX-ACCESS read-create
            STATUS current
            DESCRIPTION
                "End vlan ID."
            ::= { hwCBQoSMatchRuleCfgInfoEntry 10 }

        hwCBQoSMatchInnerSrcIp OBJECT-TYPE
            SYNTAX IpAddress
            MAX-ACCESS read-create
            STATUS current
            DESCRIPTION
                "Inner source IP address."
            ::= { hwCBQoSMatchRuleCfgInfoEntry 11 }	

        hwCBQoSMatchInnerSrcIpMask OBJECT-TYPE
            SYNTAX Unsigned32 (0..32)
            MAX-ACCESS read-create
            STATUS current
            DESCRIPTION
                "Mask length of inner source IP address, ranges from 0 to 32."
            ::= { hwCBQoSMatchRuleCfgInfoEntry 12 }	

        hwCBQoSMatchInnerDstIp OBJECT-TYPE
            SYNTAX IpAddress
            MAX-ACCESS read-create
            STATUS current
            DESCRIPTION
                "Inner destination IP address."
            ::= { hwCBQoSMatchRuleCfgInfoEntry 13 }	

        hwCBQoSMatchInnerDstIpMask OBJECT-TYPE
            SYNTAX Unsigned32 (0..32)
            MAX-ACCESS read-create
            STATUS current
            DESCRIPTION
                "Mask length of inner destination IP address, ranges from 0 to 32."
            ::= { hwCBQoSMatchRuleCfgInfoEntry 14 }	

        hwCBQoSMatchInnerSrcPort OBJECT-TYPE
            SYNTAX Unsigned32 (0..65535|65536)
            MAX-ACCESS read-create
            STATUS current
            DESCRIPTION
                "Inner source port, ranges from 0 to 65535.
		 The invalid value is 65536."
            ::= { hwCBQoSMatchRuleCfgInfoEntry 15 }	

        hwCBQoSMatchInnerDstPort OBJECT-TYPE
            SYNTAX Unsigned32 (0..65535|65536)
            MAX-ACCESS read-create
            STATUS current
            DESCRIPTION
                "Inner destination port, ranges from 0 to 65535.
		 The invalid value is 65536."
            ::= { hwCBQoSMatchRuleCfgInfoEntry 16 }	

        hwCBQoSMatchInnerProtocol OBJECT-TYPE
            SYNTAX Unsigned32 (0..255|65536)
            MAX-ACCESS read-create
            STATUS current
            DESCRIPTION
                "Inner IP protocol, ranges from 0 to 255.
		 The invalid value is 65536."
            ::= { hwCBQoSMatchRuleCfgInfoEntry 17 }
			
        hwCBQoSMatchVxlanVni OBJECT-TYPE
            SYNTAX Unsigned32 (1..16000000|0)
            MAX-ACCESS read-create
            STATUS current
            DESCRIPTION
                "Vxlan VNI, ranges from 1 to 16000000.
		 The invalid value is 0."
            ::= { hwCBQoSMatchRuleCfgInfoEntry 18 }				

        
-- hwCBQoSBehaviorObjects
        hwCBQoSBehaviorObjects OBJECT IDENTIFIER ::= { hwCBQoSObjects 2 }

        
--  Traffic Behavior Next Index
        hwCBQoSBehaviorIndexNext OBJECT-TYPE
            SYNTAX Integer32
            MAX-ACCESS read-only
            STATUS current
            DESCRIPTION
                "The value of this object identifies the index of the next available traffic behavior.
The index used when the user creates a traffic behavior must be the same as the value of hwCBQoSBehaviorIndexNext; otherwise, the traffic behavior cannot be created.
"
            ::= { hwCBQoSBehaviorObjects 1 }

        
--  Traffic Behavior
        hwCBQoSBehaviorCfgInfoTable OBJECT-TYPE
            SYNTAX SEQUENCE OF HwCBQoSBehaviorCfgInfoEntry
            MAX-ACCESS not-accessible
            STATUS current
            DESCRIPTION
                "This table is a traffic behavior configuration table that defines actions taken for traffic matching traffic classifiers."
            ::= { hwCBQoSBehaviorObjects 2 }

        
        hwCBQoSBehaviorCfgInfoEntry OBJECT-TYPE
            SYNTAX HwCBQoSBehaviorCfgInfoEntry
            MAX-ACCESS not-accessible
            STATUS current
            DESCRIPTION
                "Traffic Behavior Configuration Information Entry."
            INDEX { hwCBQoSBehaviorIndex }
            ::= { hwCBQoSBehaviorCfgInfoTable 1 }

        
        HwCBQoSBehaviorCfgInfoEntry ::=
            SEQUENCE { 
                hwCBQoSBehaviorIndex
                    Integer32,
                hwCBQoSBehaviorName
                    OCTET STRING,
                hwCBQoSBehaviorRowStatus
                    RowStatus
             }

        hwCBQoSBehaviorIndex OBJECT-TYPE
            SYNTAX Integer32
            MAX-ACCESS read-only
            STATUS current
            DESCRIPTION
                "The value of this object identifies the index of the traffic behavior.
The value ranges from 0 to 65535.
This object has no default value.
"
            ::= { hwCBQoSBehaviorCfgInfoEntry 1 }

        
        hwCBQoSBehaviorName OBJECT-TYPE
            SYNTAX OCTET STRING (SIZE (1..64))
            MAX-ACCESS read-create
            STATUS current
            DESCRIPTION
                "This object indicates the name of the traffic behavior.
The value of this object is a string of 1 to 64 visible ASCII characters, with no default value.
Space cannot exist between the characters in the string. The initial space and end space are ignored.
"
            ::= { hwCBQoSBehaviorCfgInfoEntry 2 }

        
        hwCBQoSBehaviorRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSBehaviorCfgInfoEntry 3 }

        
--  CAR
        hwCBQoSCarCfgInfoTable OBJECT-TYPE
            SYNTAX SEQUENCE OF HwCBQoSCarCfgInfoEntry
            MAX-ACCESS not-accessible
            STATUS current
            DESCRIPTION
                "This table is used to record traffic policing configurations. Rate limiting is implemented for traffic based on the table to protect customers' benefits and provide fair services."
            ::= { hwCBQoSBehaviorObjects 3 }

        
        hwCBQoSCarCfgInfoEntry OBJECT-TYPE
            SYNTAX HwCBQoSCarCfgInfoEntry
            MAX-ACCESS not-accessible
            STATUS current
            DESCRIPTION
                "CAR Configuration Information Entry."
            INDEX { hwCBQoSBehaviorIndex }
            ::= { hwCBQoSCarCfgInfoTable 1 }

        
        HwCBQoSCarCfgInfoEntry ::=
            SEQUENCE { 
                hwCBQoSCarCir
                    Unsigned32,
                hwCBQoSCarCbs
                    Unsigned32,
                hwCBQoSCarEbs
                    Unsigned32,
                hwCBQoSCarPir
                    Unsigned32,
                hwCBQoSCarPbs
                    Unsigned32,
                hwCBQoSCarGreenAction
                    CarAction,
                hwCBQoSCarGreenRemarkValue
                    Integer32,
                hwCBQoSCarYellowAction
                    CarAction,
                hwCBQoSCarYellowRemarkValue
                    Integer32,
                hwCBQoSCarRedAction
                    CarAction,
                hwCBQoSCarRedRemarkValue
                    Integer32,
                hwCBQoSCarRowStatus
                    RowStatus,
                hwCBQosCarAggregation
                    INTEGER                                   
             }

        hwCBQoSCarCir OBJECT-TYPE
            SYNTAX Unsigned32
            MAX-ACCESS read-create
            STATUS current
            DESCRIPTION
                "This object indicates the CIR. The value is an integer ranging from 0 to 4294967295, in kbit/s. There is no default value.
"
            ::= { hwCBQoSCarCfgInfoEntry 1 }

        
        hwCBQoSCarCbs OBJECT-TYPE
            SYNTAX Unsigned32
            MAX-ACCESS read-create
            STATUS current
            DESCRIPTION
                "This object indicates the CBS. The value is an integer ranging from 0 to 4294967295, in bytes. There is no default value."
            ::= { hwCBQoSCarCfgInfoEntry 2 }

        
        hwCBQoSCarEbs OBJECT-TYPE
            SYNTAX Unsigned32
            MAX-ACCESS read-create
            STATUS current
            DESCRIPTION
                "Excess Burst Size. Unit: byte. 0..19375000
                Only software QoS support this node.
                -1 is returned only when getting value from hardware QoS.
                -1 can't be set.
                "
            DEFVAL { 0 }
            ::= { hwCBQoSCarCfgInfoEntry 3 }

        
        hwCBQoSCarPir OBJECT-TYPE
            SYNTAX Unsigned32
            MAX-ACCESS read-create
            STATUS current
            DESCRIPTION
                "This object indicates the PIR. The value is an integer ranging from 0 to 4294967295, in kbit/s. There is no default value."
            ::= { hwCBQoSCarCfgInfoEntry 4 }

        
        hwCBQoSCarPbs OBJECT-TYPE
            SYNTAX Unsigned32
            MAX-ACCESS read-create
            STATUS current
            DESCRIPTION
                "This object indicates the PBS. The value is an integer ranging from 0 to 4294967295, in bytes. There is no default value.
"
            ::= { hwCBQoSCarCfgInfoEntry 5 }

        
        hwCBQoSCarGreenAction OBJECT-TYPE
            SYNTAX CarAction
            MAX-ACCESS read-create
            STATUS current
            DESCRIPTION
                "The value of this object identifies the action adopted when CIR is not reached.
                 pass (1),
                 discard (2),
                 remark IP Precedence (3),
                 remark DSCP(4),
                 remark Mpls Exp(5),
                 remark (6),
                 remark 8021p(7)
                 The default value is pass (1).
                 "
            DEFVAL { pass }
            ::= { hwCBQoSCarCfgInfoEntry 6 }

        
        hwCBQoSCarGreenRemarkValue OBJECT-TYPE
            SYNTAX Integer32 (-1 | 11..81)
            MAX-ACCESS read-create
            STATUS current
            DESCRIPTION
                "The value is to remark When green action is remarking.
                the range is 11~81;   
                the high bit represents service-class,the range is 1~8 (1:be 2:af1 3:af2 4:af3 5:af4 6:ef 7:cs6 8:cs7)
                the low bit represents color,the range is 1~3 (1:green 2:yellow 3:red)
                Only software QoS support this node.
                -1 is returned only when getting value from hardware QoS or when action being pass,discard of software QoS.
                -1 can't be set."
            ::= { hwCBQoSCarCfgInfoEntry 7 }

        
        hwCBQoSCarYellowAction OBJECT-TYPE
            SYNTAX CarAction
            MAX-ACCESS read-create
            STATUS current
            DESCRIPTION
                "The value of this object identifies the action adopted when CIR is exceeded but PIR is not reached.
                 pass (1),
                 discard (2),
                 remark IP Precedence (3),
                 remark DSCP(4),
                 remark Mpls Exp(5),
                 remark (6),
                 remark 8021p(7)
                 The default value is pass (1).
                 "
            DEFVAL { pass }
            ::= { hwCBQoSCarCfgInfoEntry 8 }

        
        hwCBQoSCarYellowRemarkValue OBJECT-TYPE
            SYNTAX Integer32 (-1 | 11..81)
            MAX-ACCESS read-create
            STATUS current
            DESCRIPTION
                "The value is to remark When yellow action is remarking.             
                For remarking DSCP, the range is 11~81; 
                the high bit represents service-class,the range is 1~8 (1:be 2:af1 3:af2 4:af3 5:af4 6:ef 7:cs6 8:cs7)
                the low bit represents color,the range is 1~3 (1:green 2:yellow 3:red)

                For remarking IP Precedence and MPLS EXP, the range is 0~7;
                Only software QoS support this node.
                -1 is returned only when getting value from hardware QoS or when action being pass,discard of software QoS.
                -1 can't be set."
            ::= { hwCBQoSCarCfgInfoEntry 9 }

        
        hwCBQoSCarRedAction OBJECT-TYPE
            SYNTAX CarAction
            MAX-ACCESS read-create
            STATUS current
            DESCRIPTION
                "The value of this object identifies the action performed when PIR is exceeded.
                 pass (1),
                 discard (2),
                 remark IP Precedence (3),
                 remark DSCP(4),
                 remark Mpls Exp(5),
                 remark (6),
                 remark 8021p(7)
                 The default value is pass (1).
                 "
            DEFVAL { discard }
            ::= { hwCBQoSCarCfgInfoEntry 10 }

        
        hwCBQoSCarRedRemarkValue OBJECT-TYPE
            SYNTAX Integer32 (-1 | 11..81)
            MAX-ACCESS read-create
            STATUS current
            DESCRIPTION
                "The value is to remark When red action is remarking.
                For remarking DSCP, the range is 11~81; 
                the high bit represents service-class,the range is 1~8 (1:be 2:af1 3:af2 4:af3 5:af4 6:ef 7:cs6 8:cs7)
                the low bit represents color,the range is 1~3 (1:green 2:yellow 3:red)
                For remarking IP Precedence and MPLS EXP, the range is 0~7;
                Only software QoS support this node.
                -1 is returned only when getting value from hardware QoS or when action being pass,discard of software QoS.
                -1 can't be set."
            ::= { hwCBQoSCarCfgInfoEntry 11 }

        hwCBQoSCarRowStatus OBJECT-TYPE
            SYNTAX RowStatus
            MAX-ACCESS read-create
            STATUS current
            DESCRIPTION
                "RowStatus. Three actions are used: active,
                createAndGo, destroy"
            ::= { hwCBQoSCarCfgInfoEntry 12 } 

            
        hwCBQosCarAggregation OBJECT-TYPE
            SYNTAX INTEGER 
            {
                aggregationCar(1),
                noneAggregationCar(2)
            }
            MAX-ACCESS read-create
            STATUS current
            DESCRIPTION
                "aggregationCar(1): aggregation car;
                 noneAggregationCar(2) : none aggregation car."
            ::= { hwCBQoSCarCfgInfoEntry 13 }
                
--  GTS
        hwCBQoSGtsCfgInfoTable OBJECT-TYPE
            SYNTAX SEQUENCE OF HwCBQoSGtsCfgInfoEntry
            MAX-ACCESS not-accessible
            STATUS current
            DESCRIPTION
                "A table of GTS feature configuration information."
            ::= { hwCBQoSBehaviorObjects 4 }

        
        hwCBQoSGtsCfgInfoEntry OBJECT-TYPE
            SYNTAX HwCBQoSGtsCfgInfoEntry
            MAX-ACCESS not-accessible
            STATUS current
            DESCRIPTION
                "GTS Configuration Information Entry."
            INDEX { hwCBQoSBehaviorIndex }
            ::= { hwCBQoSGtsCfgInfoTable 1 }

        
        HwCBQoSGtsCfgInfoEntry ::=
            SEQUENCE { 
                hwCBQoSGtsCir
                    Integer32,
                hwCBQoSGtsCbs
                    Integer32,
                hwCBQoSGtsEbs
                    Integer32,
                hwCBQoSGtsQueueLength
                    Integer32,
                hwCBQoSGtsRowStatus
                    RowStatus,
                hwCBQoSGtsPir
                    Integer32
                }

        hwCBQoSGtsCir OBJECT-TYPE
        SYNTAX Integer32 
            MAX-ACCESS read-create
            STATUS current
            DESCRIPTION
            "Committed Information Rate. Unit: kbytes"
            ::= { hwCBQoSGtsCfgInfoEntry 1 }

        
        hwCBQoSGtsCbs OBJECT-TYPE
            SYNTAX Integer32 (15000..155000000)
            MAX-ACCESS read-create
            STATUS current
            DESCRIPTION
                "Committed Burst Size. Unit: bit
                default: max(cir*1/2,15000)"
            ::= { hwCBQoSGtsCfgInfoEntry 2 }

        
        hwCBQoSGtsEbs OBJECT-TYPE
            SYNTAX Integer32 (0..155000000)
            MAX-ACCESS read-create
            STATUS current
            DESCRIPTION
                "Excess Burst Size. Unit: bit"
            DEFVAL { 0 }
            ::= { hwCBQoSGtsCfgInfoEntry 3 }

        
        hwCBQoSGtsQueueLength OBJECT-TYPE
            SYNTAX Integer32 (1..1024)
            MAX-ACCESS read-create
            STATUS current
            DESCRIPTION
                "The length of GTS buffer."
            DEFVAL { 50 }
            ::= { hwCBQoSGtsCfgInfoEntry 4 }

        
        hwCBQoSGtsRowStatus OBJECT-TYPE
            SYNTAX RowStatus
            MAX-ACCESS read-create
            STATUS current
            DESCRIPTION
                "RowStatus. Three actions are used: active,
                createAndGo, destroy"
            ::= { hwCBQoSGtsCfgInfoEntry 5 }

        
        hwCBQoSGtsPir OBJECT-TYPE
            SYNTAX Integer32 (0..155000000)
            MAX-ACCESS read-create
            STATUS current
            DESCRIPTION
                "Peak information rate."
            ::= { hwCBQoSGtsCfgInfoEntry 6 }   
            
        
--  REMARK
        hwCBQoSRemarkCfgInfoTable OBJECT-TYPE
            SYNTAX SEQUENCE OF HwCBQoSRemarkCfgInfoEntry
            MAX-ACCESS not-accessible
            STATUS current
            DESCRIPTION
                "This table is used to record flow-based re-marking configurations. Flows are classified and marked different priorities to provide differentiated services."
            ::= { hwCBQoSBehaviorObjects 5 }

        
        hwCBQoSRemarkCfgInfoEntry OBJECT-TYPE
            SYNTAX HwCBQoSRemarkCfgInfoEntry
            MAX-ACCESS not-accessible
            STATUS current
            DESCRIPTION
                "Remarking Configuration Information Entry."
            INDEX { hwCBQoSBehaviorIndex, hwCBQoSRemarkType }
            ::= { hwCBQoSRemarkCfgInfoTable 1 }

        
        HwCBQoSRemarkCfgInfoEntry ::=
            SEQUENCE { 
                hwCBQoSRemarkType
                    RemarkType,
                hwCBQoSRemarkValue
                    Integer32,
                hwCBQoSRemarkStringValue
                    OCTET STRING,
                hwCBQoSRemarkRowStatus
                    RowStatus
             }

        hwCBQoSRemarkType OBJECT-TYPE
            SYNTAX RemarkType
            MAX-ACCESS read-only
            STATUS current
            DESCRIPTION
                "The value of this object identifies the re-mark type.
                The value can be any of the following:
                IP-Prec(1)
                DSCP(2)
                MPLS-EXP(3)
                VLAN-8021p(4)
                ATM-CLP(5)
                FR-DE(6)
                QoS-Local-ID(7)
                IPV6-DSCP(8)
                Local-Prec(9)
                destination-mac(10)
                VLAN-ID(11)     
                Vlan-Protocol(12)
                This object has no default value.
                "
            ::= { hwCBQoSRemarkCfgInfoEntry 1 }

        
        hwCBQoSRemarkValue OBJECT-TYPE
            SYNTAX Integer32 (-1 | 0..63)
            MAX-ACCESS read-create
            STATUS current
            DESCRIPTION
                "The value of this object identifies the re-mark value.
When hwCBQoSRemarkType is ip-prec(1), mpls-exp(3), and vlan-8021p(4), the value ranges from 0 to 7.
When hwCBQoSRemarkType is dscp(2) or ipv6-dscp(8), the value ranges from 0 to 63.
This object has no default value.
"
            ::= { hwCBQoSRemarkCfgInfoEntry 2 }

        
        hwCBQoSRemarkStringValue OBJECT-TYPE
            SYNTAX OCTET STRING (SIZE (0..255))
            MAX-ACCESS read-create
            STATUS current
            DESCRIPTION
                "Destination-MAC(10): SIZE (0..6) HHHHHH for example: 010102020303 means the remark action is 'remark destination-mac 0101-0202-0303';
                 Vlan-Protocol(12):SIZE(3..4) HEX<600-FFFF> "
            ::= { hwCBQoSRemarkCfgInfoEntry 3 }

        
        hwCBQoSRemarkRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSRemarkCfgInfoEntry 4 }

        
--  Queue
        hwCBQoSQueueCfgInfoTable OBJECT-TYPE
            SYNTAX SEQUENCE OF HwCBQoSQueueCfgInfoEntry
            MAX-ACCESS not-accessible
            STATUS current
            DESCRIPTION
                "A table of queueing feature configuration information."
            ::= { hwCBQoSBehaviorObjects 6 }

        
        hwCBQoSQueueCfgInfoEntry OBJECT-TYPE
            SYNTAX HwCBQoSQueueCfgInfoEntry
            MAX-ACCESS not-accessible
            STATUS current
            DESCRIPTION
                "Queue Configuration Information Entry."
            INDEX { hwCBQoSBehaviorIndex }
            ::= { hwCBQoSQueueCfgInfoTable 1 }

        
        HwCBQoSQueueCfgInfoEntry ::=
            SEQUENCE { 
                hwCBQoSQueueType
                    CBQueueType,
                hwCBQoSQueueDropType
                    INTEGER,
                hwCBQoSQueueLength
                    Integer32,
                hwCBQoSQueueBandwidthUnit
                    QueueBandwidthUnit,
                hwCBQoSQueueBandwidthValue
                    Integer32,
                hwCBQoSQueueCbs
                    Integer32,
                hwCBQoSQueueQueueNumber
                    INTEGER,
                hwCBQoSQueueRowStatus
                    RowStatus,
                hwCBQoSQueueCbsRatio
                    Integer32
             }

        hwCBQoSQueueType OBJECT-TYPE
            SYNTAX CBQueueType
            MAX-ACCESS read-create
            STATUS current
            DESCRIPTION
                "Queueing Type:
                EF: (1)
                AF: (2)
                WFQ: (3)
                LLQ: (4)"
            ::= { hwCBQoSQueueCfgInfoEntry 1 }

        
        hwCBQoSQueueDropType OBJECT-TYPE
            SYNTAX INTEGER
                {
                unavailable(-1),
                tailDrop(1),
                wred(2)
                }
            MAX-ACCESS read-create
            STATUS current
            DESCRIPTION
                "The drop type of queue. Only valid for AF and WFQ queue.
                -1 is returned only when getting value about EF queue.
                -1 can't be set."
            DEFVAL { tailDrop }
            ::= { hwCBQoSQueueCfgInfoEntry 2 }

        
        hwCBQoSQueueLength OBJECT-TYPE
            SYNTAX Integer32 (-1 | 1..1024)
            MAX-ACCESS read-create
            STATUS current
            DESCRIPTION
                "The length of QueueLength. Only valid for tailDrop type
                of AF and WFQ queue.
                -1 is returned only when getting value about EF queue or wred type
                of AF and WFQ queue.
                -1 can't be set."
            DEFVAL { 64 }
            ::= { hwCBQoSQueueCfgInfoEntry 3 }

        
        hwCBQoSQueueBandwidthUnit OBJECT-TYPE
            SYNTAX QueueBandwidthUnit
            MAX-ACCESS read-create
            STATUS current
            DESCRIPTION
                "Bandwidth Unit:
                Absolute, Unit Kbps (1)
                Percent, Unit % (2)
                Only valid for EF and AF queue.
                -1 is returned only when getting value about WFQ queue.
                -1 can't be set."
            ::= { hwCBQoSQueueCfgInfoEntry 4 }

        
        hwCBQoSQueueBandwidthValue OBJECT-TYPE
            SYNTAX Integer32 (-1 | 1..1000000)
            MAX-ACCESS read-create
            STATUS current
            DESCRIPTION
                "Bandwidth value:
                Absolute value: 8~1000000. Unit: Kbps
                Percent value: 1~100.
                Only valid for EF and AF queue.
                -1 is returned only when getting value about WFQ queue.
                -1 can't be set."
            ::= { hwCBQoSQueueCfgInfoEntry 5 }

        
        hwCBQoSQueueCbs OBJECT-TYPE
            SYNTAX Integer32 (-1 | 32..2000000)
            MAX-ACCESS read-create
            STATUS current
            DESCRIPTION
                "Committed Burst Size. Unit: byte.
                Only valid for EF queue.
                -1 is returned only when getting value about AF or WFQ queue.
                -1 can't be set."
            ::= { hwCBQoSQueueCfgInfoEntry 6 }

        
        hwCBQoSQueueQueueNumber OBJECT-TYPE
            SYNTAX INTEGER
                {
                unavailable(-1),    
                a1(1),
                a8(8),              
                a16(16),
                a32(32),
                a64(64),
                a128(128),
                a256(256),
                a512(512),
                a1024(1024),
                a2048(2048),
                a4096(4096)
                }
            MAX-ACCESS read-create
            STATUS current
            DESCRIPTION
                "Max number of hashed queues (a power of 2).
                Only valid for WFQ.
                -1 is returned only when getting value about AF or EF queue.
                -1 can't be set."
            DEFVAL { a256 }
            ::= { hwCBQoSQueueCfgInfoEntry 7 }

        
        hwCBQoSQueueRowStatus OBJECT-TYPE
            SYNTAX RowStatus
            MAX-ACCESS read-create
            STATUS current
            DESCRIPTION
                "RowStatus. Three actions are used: active,
                createAndGo, destroy"
            ::= { hwCBQoSQueueCfgInfoEntry 8 }

        
        hwCBQoSQueueCbsRatio OBJECT-TYPE
            SYNTAX Integer32 (-1 | 25..500)
            MAX-ACCESS read-create
            STATUS current
            DESCRIPTION
                "Committed Burst Size Ratio. Unit: byte. CBS = CBS_Ratio * Bandwidth(k bps)
                Only valid for EF queue.
                -1 is returned only when getting value about AF or WFQ queue.
                -1 can't be set."
            DEFVAL { 25 }
            ::= { hwCBQoSQueueCfgInfoEntry 9 }

        
--  WRED
        hwCBQoSWredCfgInfoTable OBJECT-TYPE
            SYNTAX SEQUENCE OF HwCBQoSWredCfgInfoEntry
            MAX-ACCESS not-accessible
            STATUS current
            DESCRIPTION
                "A table of WRED configuration information."
            ::= { hwCBQoSBehaviorObjects 7 }

        
        hwCBQoSWredCfgInfoEntry OBJECT-TYPE
            SYNTAX HwCBQoSWredCfgInfoEntry
            MAX-ACCESS not-accessible
            STATUS current
            DESCRIPTION
                "WRED Configuration Information Entry."
            INDEX { hwCBQoSBehaviorIndex }
            ::= { hwCBQoSWredCfgInfoTable 1 }

        
        HwCBQoSWredCfgInfoEntry ::=
            SEQUENCE { 
                hwCBQoSWredType
                    WredType,
                hwCBQoSWredWeightConst
                    Integer32,
                hwCBQoSWredDropProfileIndex
                    Integer32,
                hwCBQoSWredCfgRowStatus
                    RowStatus
             }

        hwCBQoSWredType OBJECT-TYPE
            SYNTAX WredType
            MAX-ACCESS read-write
            STATUS current
            DESCRIPTION
                "IP-Prec Based (1)
                DSCP Based (2)"
            DEFVAL { ipPrecbased }
            ::= { hwCBQoSWredCfgInfoEntry 1 }

        
        hwCBQoSWredWeightConst OBJECT-TYPE
            SYNTAX Integer32 (1..16)
            MAX-ACCESS read-write
            STATUS current
            DESCRIPTION
                "Specify weight for calculating mean queue depth. "
            DEFVAL { 9 }
            ::= { hwCBQoSWredCfgInfoEntry 2 }       
            
        hwCBQoSWredDropProfileIndex OBJECT-TYPE
            SYNTAX Integer32 
            MAX-ACCESS read-write
            STATUS current
            DESCRIPTION
                "The index of wred class entry.
                 -1 is returned when no drop profile is used.
                 -1 can not be set."            
            ::= { hwCBQoSWredCfgInfoEntry 3 }

        hwCBQoSWredCfgRowStatus OBJECT-TYPE
            SYNTAX RowStatus
            MAX-ACCESS read-create
            STATUS current
            DESCRIPTION
                "RowStatus. Three actions are used: 
                 active, createAndGo, destroy"
            ::= { hwCBQoSWredCfgInfoEntry 4 }

        
--  WRED Class
        hwCBQoSWredClassCfgInfoTable OBJECT-TYPE
            SYNTAX SEQUENCE OF HwCBQoSWredClassCfgInfoEntry
            MAX-ACCESS not-accessible
            STATUS current
            DESCRIPTION
                "A table of WRED configuration information."
            ::= { hwCBQoSBehaviorObjects 8 }

        
        hwCBQoSWredClassCfgInfoEntry OBJECT-TYPE
            SYNTAX HwCBQoSWredClassCfgInfoEntry
            MAX-ACCESS not-accessible
            STATUS current
            DESCRIPTION
                "WRED Class Configuration Information Entry."
            INDEX { hwCBQoSBehaviorIndex, hwCBQoSWredClassValue }
            ::= { hwCBQoSWredClassCfgInfoTable 1 }

        
        HwCBQoSWredClassCfgInfoEntry ::=
            SEQUENCE { 
                hwCBQoSWredClassValue
                    Integer32,
                hwCBQoSWredClassLowLimit
                    Integer32,
                hwCBQoSWredClassHighLimit
                    Integer32,
                hwCBQoSWredClassDiscardProb
                    Integer32
            }        
                          
        hwCBQoSWredClassValue OBJECT-TYPE
            SYNTAX Integer32 (0..63)
            MAX-ACCESS read-only
            STATUS current
            DESCRIPTION
                "The class value.
                For IP precedence based WRED, the class is IP precedence,
                and range is 0~7.
                For DSCP based WRED, the class is DSCP, and range is 0~63."
            ::= { hwCBQoSWredClassCfgInfoEntry 1 }

        
        hwCBQoSWredClassLowLimit OBJECT-TYPE
            SYNTAX Integer32 (1..1024)
            MAX-ACCESS read-write
            STATUS current
            DESCRIPTION
                "The low limit of queue depth."
            DEFVAL { 10 }
            ::= { hwCBQoSWredClassCfgInfoEntry 2 }

        
        hwCBQoSWredClassHighLimit OBJECT-TYPE
            SYNTAX Integer32 (1..1024)
            MAX-ACCESS read-write
            STATUS current
            DESCRIPTION
                "The high limit of queue depth."
            DEFVAL { 30 }
            ::= { hwCBQoSWredClassCfgInfoEntry 3 }

        
        hwCBQoSWredClassDiscardProb OBJECT-TYPE
            SYNTAX Integer32 (1..255)
            MAX-ACCESS read-write
            STATUS current
            DESCRIPTION
                "The discard probability denominator."
            DEFVAL { 10 }
            ::= { hwCBQoSWredClassCfgInfoEntry 4 } 
                        
        
--  NAT
        hwCBQoSNatCfgInfoTable OBJECT-TYPE
            SYNTAX SEQUENCE OF HwCBQoSNatCfgInfoEntry
            MAX-ACCESS not-accessible
            STATUS current
            DESCRIPTION
                "A table of Nat configuration information."
            ::= { hwCBQoSBehaviorObjects 10 }

        
        hwCBQoSNatCfgInfoEntry OBJECT-TYPE
            SYNTAX HwCBQoSNatCfgInfoEntry
            MAX-ACCESS not-accessible
            STATUS current
            DESCRIPTION
                "Nat Configuration Information Entry."
            INDEX { hwCBQoSBehaviorIndex }
            ::= { hwCBQoSNatCfgInfoTable 1 }

        
        HwCBQoSNatCfgInfoEntry ::=
            SEQUENCE { 
                hwCBQoSNatAddressGroup
                    OCTET STRING,
                hwCBQoSNatNoPat
                    INTEGER,
                hwCBQoSNatServiceClass
                    Integer32,
                hwCBQoSNatRowStatus
                    RowStatus
             }

        hwCBQoSNatAddressGroup OBJECT-TYPE
            SYNTAX OCTET STRING (SIZE (1..31))
            MAX-ACCESS read-create
            STATUS current
            DESCRIPTION
                "address group's name"
            ::= { hwCBQoSNatCfgInfoEntry 1 }

        
        hwCBQoSNatNoPat OBJECT-TYPE
            SYNTAX INTEGER
                {
                nopat(1),
                pat(2)
                }
            MAX-ACCESS read-create
            STATUS current
            DESCRIPTION
                "1: no pat
                2: pat"
            ::= { hwCBQoSNatCfgInfoEntry 2 }

        
        hwCBQoSNatServiceClass OBJECT-TYPE
            SYNTAX Integer32 (1..4)
            MAX-ACCESS read-create
            STATUS current
            DESCRIPTION
                "The service class. DEFVAL: 2"
            DEFVAL { 2 }
            ::= { hwCBQoSNatCfgInfoEntry 3 }

        
        hwCBQoSNatRowStatus OBJECT-TYPE
            SYNTAX RowStatus
            MAX-ACCESS read-create
            STATUS current
            DESCRIPTION
                "RowStatus. Three actions are used: active,
                createAndGo, destroy"
            ::= { hwCBQoSNatCfgInfoEntry 4 }

        
--  Firewall
        hwCBQoSFirewallCfgInfoTable OBJECT-TYPE
            SYNTAX SEQUENCE OF HwCBQoSFirewallCfgInfoEntry
            MAX-ACCESS not-accessible
            STATUS current
            DESCRIPTION
                "A table of Firewall configuration information."
            ::= { hwCBQoSBehaviorObjects 11 }

        
        hwCBQoSFirewallCfgInfoEntry OBJECT-TYPE
            SYNTAX HwCBQoSFirewallCfgInfoEntry
            MAX-ACCESS not-accessible
            STATUS current
            DESCRIPTION
                "Firewall Configuration Information Entry."
            INDEX { hwCBQoSBehaviorIndex }
            ::= { hwCBQoSFirewallCfgInfoTable 1 }

        
        HwCBQoSFirewallCfgInfoEntry ::=
            SEQUENCE { 
                hwCBQoSFirewallAction
                    INTEGER,
                hwCBQoSFirewallRowStatus
                    RowStatus
             }

        hwCBQoSFirewallAction OBJECT-TYPE
            SYNTAX INTEGER
                {
                permit(1),
                deny(2)
                }
            MAX-ACCESS read-create
            STATUS current
            DESCRIPTION
                "The value of this object identifies the firewall action.
The value can be permit(1) or deny(2).
The default value is permit(1).
"
            DEFVAL { permit }
            ::= { hwCBQoSFirewallCfgInfoEntry 1 }

        
        hwCBQoSFirewallRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSFirewallCfgInfoEntry 2 }

        
--  Sampling behavior
        hwCBQoSSamplingCfgInfoTable OBJECT-TYPE
            SYNTAX SEQUENCE OF HwCBQoSSamplingCfgInfoEntry
            MAX-ACCESS not-accessible
            STATUS current
            DESCRIPTION
                "A table of Sampling configuration information."
            ::= { hwCBQoSBehaviorObjects 12 }

        
        hwCBQoSSamplingCfgInfoEntry OBJECT-TYPE
            SYNTAX HwCBQoSSamplingCfgInfoEntry
            MAX-ACCESS not-accessible
            STATUS current
            DESCRIPTION
                "Sampling Configuration Information Entry."
            INDEX { hwCBQoSBehaviorIndex }
            ::= { hwCBQoSSamplingCfgInfoTable 1 }

        
        HwCBQoSSamplingCfgInfoEntry ::=
            SEQUENCE { 
                hwCBQoSIfSamplingType
                    SamplingType,
                hwCBQoSSamplingNum
                    Integer32,
                hwCBQoSSamplingRowStatus
                    RowStatus
             }

        hwCBQoSIfSamplingType OBJECT-TYPE
            SYNTAX SamplingType
            MAX-ACCESS read-create
            STATUS current
            DESCRIPTION
                "This object indicates the sampling type.
The value can be any of the following:
Fix-packets(1)
Fix-time(2)
Random-packets(3)
Random-time(4)
This object has no default value.
"
            ::= { hwCBQoSSamplingCfgInfoEntry 1 }

        
        hwCBQoSSamplingNum OBJECT-TYPE
            SYNTAX Integer32 (1..65535)
            MAX-ACCESS read-create
            STATUS current
            DESCRIPTION
                "This object indicates the sampling parameter.
The value can be any of the following:
Fix-packets (1-65535)
Fix-time (5-30000ms)
Random-packets (1-65535)
Random-time (3/6/12/24/48/96/192/383.5/767/1534/3068/6136ms)
This object has no default value.
"
            ::= { hwCBQoSSamplingCfgInfoEntry 2 }

        
        hwCBQoSSamplingRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSSamplingCfgInfoEntry 3 }

        
--  LR
        hwCBQoSLrCfgInfoTable OBJECT-TYPE
            SYNTAX SEQUENCE OF HwCBQoSLrCfgInfoEntry
            MAX-ACCESS not-accessible
            STATUS current
            DESCRIPTION
                "A table of Line Rate configuration information."
            ::= { hwCBQoSBehaviorObjects 13 }

        
        hwCBQoSLrCfgInfoEntry OBJECT-TYPE
            SYNTAX HwCBQoSLrCfgInfoEntry
            MAX-ACCESS not-accessible
            STATUS current
            DESCRIPTION
                "LR Configuration Information Entry."
            INDEX { hwCBQoSBehaviorIndex }
            ::= { hwCBQoSLrCfgInfoTable 1 }

        
        HwCBQoSLrCfgInfoEntry ::=
            SEQUENCE { 
                hwCBQoSLrUnit
                    LrCirUnit,
                hwCBQoSLrCir
                    Integer32,
                hwCBQoSLrCbs
                    Integer32,
                hwCBQoSLrEbs
                    Integer32,
                hwCBQoSLrRowStatus
                    RowStatus
             }

        hwCBQoSLrUnit OBJECT-TYPE
            SYNTAX LrCirUnit
            MAX-ACCESS read-create
            STATUS current
            DESCRIPTION
                "CIR Unit:
                Absolute, Unit bps (1)
                Percent, Unit % (2)"
            ::= { hwCBQoSLrCfgInfoEntry 1 }

        
        hwCBQoSLrCir OBJECT-TYPE
            SYNTAX Integer32 (1..155000000)
            MAX-ACCESS read-create
            STATUS current
            DESCRIPTION
                "Committed Information Rate.
                Absolute value: 8000..155000000. Unit: bps
                Percent value: 1~100."
            ::= { hwCBQoSLrCfgInfoEntry 2 }

        
        hwCBQoSLrCbs OBJECT-TYPE
            SYNTAX Integer32 (50..155000000)
            MAX-ACCESS read-create
            STATUS current
            DESCRIPTION
                "Committed Burst Size.
                When CIR is absolute value,
                CBS value: 15000..155000000,
                default value: max(cir*1/2,15000),
                Unit: bit;
                When CIR is percent value,
                CBS value: 50..2000,
                default value: 500,
                Unit: ms.
                "
            ::= { hwCBQoSLrCfgInfoEntry 3 }

        
        hwCBQoSLrEbs OBJECT-TYPE
            SYNTAX Integer32 (0..155000000)
            MAX-ACCESS read-create
            STATUS current
            DESCRIPTION
                "Excess Burst Size.
                When CIR is absolute value,
                EBS value: 0..155000000, Unit: bit;
                When CIR is percent value,
                EBS value: 0..2000, Unit: ms."
            DEFVAL { 0 }
            ::= { hwCBQoSLrCfgInfoEntry 4 }

        
        hwCBQoSLrRowStatus OBJECT-TYPE
            SYNTAX RowStatus
            MAX-ACCESS read-create
            STATUS current
            DESCRIPTION
                "RowStatus. Three actions are used: active,
                createAndGo, destroy"
            ::= { hwCBQoSLrCfgInfoEntry 5 }

        
--  Hierachical Policy
        hwCBQoSNestPolicyCfgInfoTable OBJECT-TYPE
            SYNTAX SEQUENCE OF HwCBQoSNestPolicyCfgInfoEntry
            MAX-ACCESS not-accessible
            STATUS current
            DESCRIPTION
                "A table of Hierachical Policy configuration information."
            ::= { hwCBQoSBehaviorObjects 14 }

        
        hwCBQoSNestPolicyCfgInfoEntry OBJECT-TYPE
            SYNTAX HwCBQoSNestPolicyCfgInfoEntry
            MAX-ACCESS not-accessible
            STATUS current
            DESCRIPTION
                "Hierachical Policy Configuration Information Entry."
            INDEX { hwCBQoSBehaviorIndex }
            ::= { hwCBQoSNestPolicyCfgInfoTable 1 }

        
        HwCBQoSNestPolicyCfgInfoEntry ::=
            SEQUENCE { 
                hwCBQoSNestPolicyName
                    OCTET STRING,
                hwCBQoSNestPolicyRowStatus
                    RowStatus
             }

        hwCBQoSNestPolicyName OBJECT-TYPE
            SYNTAX OCTET STRING (SIZE (1..31))
            MAX-ACCESS read-create
            STATUS current
            DESCRIPTION
                "Name of hierachical traffic policy."
            ::= { hwCBQoSNestPolicyCfgInfoEntry 1 }

        
        hwCBQoSNestPolicyRowStatus OBJECT-TYPE
            SYNTAX RowStatus
            MAX-ACCESS read-create
            STATUS current
            DESCRIPTION
                "RowStatus. Three actions are used: active,
                createAndGo, destroy"
            ::= { hwCBQoSNestPolicyCfgInfoEntry 2 }

        
--  Redirect behavior
        hwCBQoSRedirectCfgInfoTable OBJECT-TYPE
            SYNTAX SEQUENCE OF HwCBQoSRedirectCfgInfoEntry
            MAX-ACCESS not-accessible
            STATUS current
            DESCRIPTION
                "A table of Redirect configuration information."
            ::= { hwCBQoSBehaviorObjects 15 }

        
        hwCBQoSRedirectCfgInfoEntry OBJECT-TYPE
            SYNTAX HwCBQoSRedirectCfgInfoEntry
            MAX-ACCESS not-accessible
            STATUS current
            DESCRIPTION
                "Redirect Configuration Information Entry."
            INDEX { hwCBQoSBehaviorIndex, hwCBQoSRedirectType }
            ::= { hwCBQoSRedirectCfgInfoTable 1 }

        
        HwCBQoSRedirectCfgInfoEntry ::=
            SEQUENCE { 
                hwCBQoSRedirectType
                    RedirectType,
                hwCBQoSRedirectIpAddress
                    OCTET STRING,
                hwCBQoSRedirectIfIndex
                    Integer32,
                hwCBQoSRedirectVlanId
                    Integer32,
                hwCBQoSRedirectCtrlType
                    RedirectCtrlType,
                hwCBQoSRedirectRowStatus
                    RowStatus,
                hwCBQoSRedirectLSPDstIpAddress
                    OCTET STRING,
                hwCBQoSRedirectLSPSecondary
                    INTEGER
             }

        hwCBQoSRedirectType OBJECT-TYPE
            SYNTAX RedirectType
            MAX-ACCESS read-only
            STATUS current
            DESCRIPTION
                "The value of this object identifies the traffic redirection type.
The value can be ip-nexthop(2), ipv6-nexthop(5), or lsppath(6).
This object has no default value.
"
            ::= { hwCBQoSRedirectCfgInfoEntry 1 }

        
        hwCBQoSRedirectIpAddress OBJECT-TYPE
            SYNTAX OCTET STRING (SIZE (0..31))
            MAX-ACCESS read-create
            STATUS current
            DESCRIPTION
                "This object indicates the destination address of the redirected traffic.
The value of this object can be any valid IP address.This object has no default value.                                             
"
            ::= { hwCBQoSRedirectCfgInfoEntry 2 }

        
        hwCBQoSRedirectIfIndex OBJECT-TYPE
            SYNTAX Integer32
            MAX-ACCESS read-create
            STATUS current
            DESCRIPTION
                "The value of this object identifies the outbound interface of the redirected traffic.
This object has no value range, and the default value is 0.The outbound interface cannot be an interface of the Main Processing Unit (MPU) or a Layer 2 interface.
The value 0 indicates that no outbound interface is specified.
"
            ::= { hwCBQoSRedirectCfgInfoEntry 3 }

        
        hwCBQoSRedirectVlanId OBJECT-TYPE
            SYNTAX Integer32 (-1 | 0 | 2..4094)
            MAX-ACCESS read-create
            STATUS current
            DESCRIPTION
                "The value of this object identifies the VLAN ID of the outbound interface of the redirected traffic."
            ::= { hwCBQoSRedirectCfgInfoEntry 4 }

        
        hwCBQoSRedirectCtrlType OBJECT-TYPE
            SYNTAX RedirectCtrlType
            MAX-ACCESS read-create
            STATUS current
            DESCRIPTION
                "The value of this object identifies the traffic redirection control type."
            ::= { hwCBQoSRedirectCfgInfoEntry 5 }

        
        hwCBQoSRedirectRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSRedirectCfgInfoEntry 6 }

        
        hwCBQoSRedirectLSPDstIpAddress OBJECT-TYPE
            SYNTAX OCTET STRING (SIZE (0..31))
            MAX-ACCESS read-create
            STATUS current
            DESCRIPTION
                "This object indicates the next hop of an LSP.
The value of this object can be any valid IP address.
This object has no default value.
"
            ::= { hwCBQoSRedirectCfgInfoEntry 7 }

        
        hwCBQoSRedirectLSPSecondary OBJECT-TYPE
            SYNTAX INTEGER
                {
                notConfigLSP(-1),
                mainLSPPath(1),
                backupLSPPath(2)
                }
            MAX-ACCESS read-create
            STATUS current
            DESCRIPTION
                "The value of this object identifies whether a primary or a standby LSP is used.
The value can be mainLSPPath(1) or backupLSPPath(2).
The default value is mainLSPPath(1).
"
            DEFVAL { mainLSPPath }
            ::= { hwCBQoSRedirectCfgInfoEntry 8 }

        
--  mirror behavior
        hwCBQoSMirrorCfgInfoTable OBJECT-TYPE
            SYNTAX SEQUENCE OF HwCBQoSMirrorCfgInfoEntry
            MAX-ACCESS not-accessible
            STATUS current
            DESCRIPTION
                "A table of Mirror configuration information."
            ::= { hwCBQoSBehaviorObjects 16 }

        
        hwCBQoSMirrorCfgInfoEntry OBJECT-TYPE
            SYNTAX HwCBQoSMirrorCfgInfoEntry
            MAX-ACCESS not-accessible
            STATUS current
            DESCRIPTION
                "Mirror Configuration Information Entry."
            INDEX { hwCBQoSBehaviorIndex }
            ::= { hwCBQoSMirrorCfgInfoTable 1 }

        
        HwCBQoSMirrorCfgInfoEntry ::=
            SEQUENCE { 
                hwCBQoSMirrorObserveIndex
                    Integer32,
                hwCBQoSMirrorRowStatus
                    RowStatus
             }

        hwCBQoSMirrorObserveIndex OBJECT-TYPE
            SYNTAX Integer32 (1..16)
            MAX-ACCESS read-create
            STATUS current
            DESCRIPTION
                "The mirror observe port number"
            ::= { hwCBQoSMirrorCfgInfoEntry 1 }

        
        hwCBQoSMirrorRowStatus OBJECT-TYPE
            SYNTAX RowStatus
            MAX-ACCESS read-create
            STATUS current
            DESCRIPTION
                "RowStatus. Three actions are used: active,
                createAndGo, destroy"
            ::= { hwCBQoSMirrorCfgInfoEntry 2 }

        
--  Urpf behavior
        hwCBQoSUrpfCfgInfoTable OBJECT-TYPE
            SYNTAX SEQUENCE OF HwCBQoSUrpfCfgInfoEntry
            MAX-ACCESS not-accessible
            STATUS current
            DESCRIPTION
                "A table of Urpf configuration information."
            ::= { hwCBQoSBehaviorObjects 17 }

        
        hwCBQoSUrpfCfgInfoEntry OBJECT-TYPE
            SYNTAX HwCBQoSUrpfCfgInfoEntry
            MAX-ACCESS not-accessible
            STATUS current
            DESCRIPTION
                "Urpf Configuration Information Entry."
            INDEX { hwCBQoSBehaviorIndex }
            ::= { hwCBQoSUrpfCfgInfoTable 1 }

        
        HwCBQoSUrpfCfgInfoEntry ::=
            SEQUENCE { 
                hwCBQoSUrpfCtrlType
                    UrpfCtrlType,
                hwCBQoSUrpfAllowDefault
                    Integer32,
                hwCBQoSUrpfRowStatus
                    RowStatus
             }

        hwCBQoSUrpfCtrlType OBJECT-TYPE
            SYNTAX UrpfCtrlType
            MAX-ACCESS read-create
            STATUS current
            DESCRIPTION
                "The value of this object identifies URPF control type.
The value can be strict(1) or loose(2).
This object has no default value.
"
            ::= { hwCBQoSUrpfCfgInfoEntry 1 }

        
        hwCBQoSUrpfAllowDefault OBJECT-TYPE
            SYNTAX Integer32 (0..1)
            MAX-ACCESS read-create
            STATUS current
            DESCRIPTION
                "The value of this object identifies whether URPF flags the default route.
The value can be 0 or 1.
0: indicates that the default route is not allowed.
1: indicates that the default route is allowed.
The default value is 1.
"
            ::= { hwCBQoSUrpfCfgInfoEntry 2 }

        
        hwCBQoSUrpfRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSUrpfCfgInfoEntry 3 }

        
--  Count
        hwCBQoSCountCfgInfoTable OBJECT-TYPE
            SYNTAX SEQUENCE OF HwCBQoSCountCfgInfoEntry
            MAX-ACCESS not-accessible
            STATUS current
            DESCRIPTION
                "A table of Count configuration information."
            ::= { hwCBQoSBehaviorObjects 18 }

        
        hwCBQoSCountCfgInfoEntry OBJECT-TYPE
            SYNTAX HwCBQoSCountCfgInfoEntry
            MAX-ACCESS not-accessible
            STATUS current
            DESCRIPTION
                "Count Configuration Information Entry."
            INDEX { hwCBQoSBehaviorIndex }
            ::= { hwCBQoSCountCfgInfoTable 1 }

        
        HwCBQoSCountCfgInfoEntry ::=
            SEQUENCE { 
                hwCBQoSCountAction
                    INTEGER,
                hwCBQoSCountRowStatus
                    RowStatus
             }

        hwCBQoSCountAction OBJECT-TYPE
            SYNTAX INTEGER { count(1) }
            MAX-ACCESS read-create
            STATUS current
            DESCRIPTION
                "The Count action "
            ::= { hwCBQoSCountCfgInfoEntry 1 }

        
        hwCBQoSCountRowStatus OBJECT-TYPE
            SYNTAX RowStatus
            MAX-ACCESS read-create
            STATUS current
            DESCRIPTION
                "RowStatus. Three actions are used: active,
                createAndGo, destroy"
            ::= { hwCBQoSCountCfgInfoEntry 2 }

        
--  Drop
        hwCBQoSHighDropCfgInfoTable OBJECT-TYPE
            SYNTAX SEQUENCE OF HwCBQoSHighDropCfgInfoEntry
            MAX-ACCESS not-accessible
            STATUS current
            DESCRIPTION
                "A table of Drop configuration information."
            ::= { hwCBQoSBehaviorObjects 19 }

        
        hwCBQoSHighDropCfgInfoEntry OBJECT-TYPE
            SYNTAX HwCBQoSHighDropCfgInfoEntry
            MAX-ACCESS not-accessible
            STATUS current
            DESCRIPTION
                "Drop Configuration Information Entry."
            INDEX { hwCBQoSBehaviorIndex }
            ::= { hwCBQoSHighDropCfgInfoTable 1 }

        
        HwCBQoSHighDropCfgInfoEntry ::=
            SEQUENCE { 
                hwCBQoSHighDropPrecedence
                    INTEGER,
                hwCBQoSHighDropRowStatus
                    RowStatus
             }

        hwCBQoSHighDropPrecedence OBJECT-TYPE
            SYNTAX INTEGER { high(1) }
            MAX-ACCESS read-create
            STATUS current
            DESCRIPTION
                "The Drop Precedence "
            ::= { hwCBQoSHighDropCfgInfoEntry 1 }

        
        hwCBQoSHighDropRowStatus OBJECT-TYPE
            SYNTAX RowStatus
            MAX-ACCESS read-create
            STATUS current
            DESCRIPTION
                "RowStatus. Three actions are used: active,
                createAndGo, destroy"
            ::= { hwCBQoSHighDropCfgInfoEntry 2 }

        
--  Load balance method selection behavior
        hwCBQoSLoadBalanceCfgInfoTable OBJECT-TYPE
            SYNTAX SEQUENCE OF HwCBQoSLoadBalanceCfgInfoEntry
            MAX-ACCESS not-accessible
            STATUS current
            DESCRIPTION
                "A table of configuring load balance method."
            ::= { hwCBQoSBehaviorObjects 20 }

        
        hwCBQoSLoadBalanceCfgInfoEntry OBJECT-TYPE
            SYNTAX HwCBQoSLoadBalanceCfgInfoEntry
            MAX-ACCESS not-accessible
            STATUS current
            DESCRIPTION
                "Load Balance Configuration Information Entry."
            INDEX { hwCBQoSBehaviorIndex }
            ::= { hwCBQoSLoadBalanceCfgInfoTable 1 }

        
        HwCBQoSLoadBalanceCfgInfoEntry ::=
            SEQUENCE { 
                hwCBQoSLoadBalanceType
                    INTEGER,
                hwCBQoSLoadBalanceRowStatus
                    RowStatus
             }

        hwCBQoSLoadBalanceType OBJECT-TYPE
            SYNTAX INTEGER
                {
                flow(1),
                packet(2)
                }
            MAX-ACCESS read-create
            STATUS current
            DESCRIPTION
                "The value of this object identifies the type of the algorithm for load balancing.
The value can be flow(1) or packet(2).
The default value is flow(1). 
"
            ::= { hwCBQoSLoadBalanceCfgInfoEntry 1 }

        
        hwCBQoSLoadBalanceRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSLoadBalanceCfgInfoEntry 2 }

    --Egress Gts 
    hwCBQoSEgressGtsCfgInfoTable OBJECT-TYPE
        SYNTAX SEQUENCE OF HwCBQoSEgressGtsCfgInfoEntry
        MAX-ACCESS not-accessible
        STATUS current
        DESCRIPTION
            "A table of Egress GTS feature configuration information."
        ::= { hwCBQoSBehaviorObjects 21 }  
        
     hwCBQoSEgressGtsCfgInfoEntry OBJECT-TYPE
        SYNTAX HwCBQoSEgressGtsCfgInfoEntry
        MAX-ACCESS not-accessible
        STATUS current
        DESCRIPTION
            "Egress GTS feature configuration information Entry."
        INDEX {hwCBQoSBehaviorIndex,hwCBQoSEgressGtsIfIndex }
        ::= { hwCBQoSEgressGtsCfgInfoTable 1 }        
        
     HwCBQoSEgressGtsCfgInfoEntry ::=
        SEQUENCE { 
            hwCBQoSEgressGtsIfIndex
                InterfaceIndex,
            hwCBQoSEgressGtsCir
                Integer32,
            hwCBQoSEgressGtsPir
                Integer32,
            hwCBQoSEgressGtsRowStatus   
                RowStatus               
            }

    hwCBQoSEgressGtsIfIndex OBJECT-TYPE
        SYNTAX InterfaceIndex
        MAX-ACCESS not-accessible
        STATUS current
        DESCRIPTION    
            "Interface index.  "
        ::= { hwCBQoSEgressGtsCfgInfoEntry 1 }             
        
    hwCBQoSEgressGtsCir OBJECT-TYPE
        SYNTAX Integer32 
        MAX-ACCESS read-create
        STATUS current
        DESCRIPTION
            "Committed Information Rate. Unit: kbps"
        ::= { hwCBQoSEgressGtsCfgInfoEntry 2 }
            
    hwCBQoSEgressGtsPir OBJECT-TYPE
        SYNTAX Integer32 
        MAX-ACCESS read-create
        STATUS current
        DESCRIPTION
            "Peak information rate. Unit: kbps"
        ::= { hwCBQoSEgressGtsCfgInfoEntry 3 }        
        
    hwCBQoSEgressGtsRowStatus OBJECT-TYPE
        SYNTAX RowStatus
        MAX-ACCESS read-create
        STATUS current
        DESCRIPTION
            "RowStatus. Three actions are used: active,
        createAndGo, destroy"
        ::= { hwCBQoSEgressGtsCfgInfoEntry 4 }    
        
                                
     ---Service-class                 
        hwCBQoSServiceClassCfgInfoTable OBJECT-TYPE
            SYNTAX SEQUENCE OF HwCBQoSServiceClassCfgInfoEntry
            MAX-ACCESS not-accessible
            STATUS current
            DESCRIPTION
                "This table is used to record service class configurations."
            ::= { hwCBQoSBehaviorObjects 22 }

        
        hwCBQoSServiceClassCfgInfoEntry OBJECT-TYPE
            SYNTAX HwCBQoSServiceClassCfgInfoEntry
            MAX-ACCESS not-accessible
            STATUS current
            DESCRIPTION
                "ServiceClass feature configuration information Entry."
            INDEX { hwCBQoSBehaviorIndex }
            ::= { hwCBQoSServiceClassCfgInfoTable 1 }

        
        HwCBQoSServiceClassCfgInfoEntry ::=
            SEQUENCE { 
                hwCBQoSServiceClassQueueId
                    CosType,
                hwCBQoSServiceClassColor
                    INTEGER,    
                hwCBQoSServiceClassRowStatus
                    RowStatus,
                hwCBQoSServiceClassNoremarkflag
                    Integer32    
             }

        hwCBQoSServiceClassQueueId OBJECT-TYPE
            SYNTAX CosType
            MAX-ACCESS read-create
            STATUS current
            DESCRIPTION
                 "Indicates the queue ID."
            ::= { hwCBQoSServiceClassCfgInfoEntry 1 }

        
        hwCBQoSServiceClassColor OBJECT-TYPE
            SYNTAX INTEGER 
            {
             green(1),
             yellow(2),
             red(3)
            }            
            MAX-ACCESS read-create
            STATUS current
            DESCRIPTION
                "Indicates the color."
            ::= { hwCBQoSServiceClassCfgInfoEntry 2 }  
            
        hwCBQoSServiceClassRowStatus OBJECT-TYPE
            SYNTAX RowStatus 
            MAX-ACCESS read-create
            STATUS current
            DESCRIPTION
                "RowStatus. Three actions are used: active,
                createAndGo, destroy"
            ::= { hwCBQoSServiceClassCfgInfoEntry 3 }    
        
       	hwCBQoSServiceClassNoremarkflag OBJECT-TYPE
            SYNTAX Integer32 
            MAX-ACCESS read-create
            STATUS current
            DESCRIPTION
                "QOS service class no remark flag. "
            ::= { hwCBQoSServiceClassCfgInfoEntry 4 }  
              
     ---RedirectMUL behavior
        hwCBQoSRedirectMULCfgInfoTable OBJECT-TYPE
            SYNTAX SEQUENCE OF HwCBQoSRedirectMULCfgInfoEntry
            MAX-ACCESS not-accessible
            STATUS current
            DESCRIPTION
                "A table of Redirect MultiNHP configuration information."
            ::= { hwCBQoSBehaviorObjects 23 }

        
        hwCBQoSRedirectMULCfgInfoEntry OBJECT-TYPE
            SYNTAX HwCBQoSRedirectMULCfgInfoEntry
            MAX-ACCESS not-accessible
            STATUS current
            DESCRIPTION
                "Redirect MultiNHP Configuration Information Entry."
            INDEX { hwCBQoSBehaviorIndex }
            ::= { hwCBQoSRedirectMULCfgInfoTable 1 }

        
        HwCBQoSRedirectMULCfgInfoEntry ::=
            SEQUENCE {
                hwCBQoSRedirectMULIpAddress1
                    OCTET STRING,
                hwCBQoSRedirectMULIfIndex1
                    Integer32,
                hwCBQoSRedirectMULIpAddress2
                    OCTET STRING,
                hwCBQoSRedirectMULIfIndex2
                    Integer32,
                hwCBQoSRedirectMULIpAddress3
                    OCTET STRING,
                hwCBQoSRedirectMULIfIndex3
                    Integer32,
                hwCBQoSRedirectMULIpAddress4
                    OCTET STRING,
                hwCBQoSRedirectMULIfIndex4
                    Integer32,                
                hwCBQoSRedirectMULCtrlType
                    RedirectCtrlType,
                hwCBQoSRedirectMULRowStatus   
                    RowStatus
             }
                     
        hwCBQoSRedirectMULIpAddress1 OBJECT-TYPE
            SYNTAX OCTET STRING (SIZE (0..31))
            MAX-ACCESS read-create
            STATUS current
            DESCRIPTION
                "Indicates the first available next-hop IP address."
            ::= { hwCBQoSRedirectMULCfgInfoEntry 1 }

        
        hwCBQoSRedirectMULIfIndex1 OBJECT-TYPE
            SYNTAX Integer32
            MAX-ACCESS read-create
            STATUS current
            DESCRIPTION
                "Indicates the first available next-hop outbound interface."
            ::= { hwCBQoSRedirectMULCfgInfoEntry 2 }
            
        
        hwCBQoSRedirectMULIpAddress2 OBJECT-TYPE
            SYNTAX OCTET STRING (SIZE (0..31))
            MAX-ACCESS read-create
            STATUS current
            DESCRIPTION
                "Indicates the second available next-hop IP address."
            ::= { hwCBQoSRedirectMULCfgInfoEntry 3 }

        
        hwCBQoSRedirectMULIfIndex2 OBJECT-TYPE
            SYNTAX Integer32
            MAX-ACCESS read-create
            STATUS current
            DESCRIPTION
                "Indicates the second available next-hop outbound interface."
            ::= { hwCBQoSRedirectMULCfgInfoEntry 4 }
            
            
        hwCBQoSRedirectMULIpAddress3 OBJECT-TYPE
            SYNTAX OCTET STRING (SIZE (0..31))
            MAX-ACCESS read-create
            STATUS current
            DESCRIPTION
                "Indicates the third available next-hop IP address."
            ::= { hwCBQoSRedirectMULCfgInfoEntry 5 }

        
        hwCBQoSRedirectMULIfIndex3 OBJECT-TYPE
            SYNTAX Integer32
            MAX-ACCESS read-create
            STATUS current
            DESCRIPTION
                "Indicates the third available next-hop outbound interface."
            ::= { hwCBQoSRedirectMULCfgInfoEntry 6 }
            
            
        hwCBQoSRedirectMULIpAddress4 OBJECT-TYPE
            SYNTAX OCTET STRING (SIZE (0..31))
            MAX-ACCESS read-create
            STATUS current
            DESCRIPTION
                "Indicates the fourth available next-hop IP address."
            ::= { hwCBQoSRedirectMULCfgInfoEntry 7 }

        
        hwCBQoSRedirectMULIfIndex4 OBJECT-TYPE
            SYNTAX Integer32
            MAX-ACCESS read-create
            STATUS current
            DESCRIPTION
                "Indicates the fourth available next-hop outbound interface."
            ::= { hwCBQoSRedirectMULCfgInfoEntry 8 }   
            
                    
        hwCBQoSRedirectMULCtrlType OBJECT-TYPE
            SYNTAX RedirectCtrlType
            MAX-ACCESS read-create
            STATUS current
            DESCRIPTION
                "Indicates the redirection type."
            ::= { hwCBQoSRedirectMULCfgInfoEntry 9 }

        
        hwCBQoSRedirectMULRowStatus OBJECT-TYPE
            SYNTAX RowStatus
            MAX-ACCESS read-create
            STATUS current
            DESCRIPTION
                "Indicates the row status."
            ::= { hwCBQoSRedirectMULCfgInfoEntry 10 }              
              
       hwCBQoSRandomDiscardCfgInfoTable OBJECT-TYPE
             SYNTAX SEQUENCE OF HwCBQoSRandomDiscardCfgInfoEntry
             MAX-ACCESS not-accessible
             STATUS current
             DESCRIPTION
                  "Description."
                 ::= { hwCBQoSBehaviorObjects 24 }

      hwCBQoSRandomDiscardCfgInfoEntry OBJECT-TYPE
            SYNTAX HwCBQoSRandomDiscardCfgInfoEntry
            MAX-ACCESS not-accessible
            STATUS current
            DESCRIPTION
                "Description."
            INDEX { hwCBQoSBehaviorIndex }
            ::= { hwCBQoSRandomDiscardCfgInfoTable 1 }


       HwCBQoSRandomDiscardCfgInfoEntry ::=
            SEQUENCE { 
            hwCBQoSRandomPercent
                            Integer32,
                        hwCBQoSRandomDiscardRowStatus
                            RowStatus
                     }
    
    
            hwCBQoSRandomPercent OBJECT-TYPE
                    SYNTAX Integer32 (1..99)
                    MAX-ACCESS read-create
                    STATUS current
                    DESCRIPTION
                        "Description."
                    ::= { hwCBQoSRandomDiscardCfgInfoEntry 1 }
    
            
            hwCBQoSRandomDiscardRowStatus OBJECT-TYPE
                    SYNTAX RowStatus
                    MAX-ACCESS read-create
                    STATUS current
                    DESCRIPTION
                        "Description."
                    ::= { hwCBQoSRandomDiscardCfgInfoEntry 50 }
    
            
    --  1.3.6.1.4.1.2011.5.25.32.1.1.2.25
            -- 1.3.6.1.4.1.2011.5.25.32.1.1.2.25
            hwCBQoSDenyPacketLengthCfgInfoTable OBJECT-TYPE
                SYNTAX SEQUENCE OF HwCBQoSDenyPacketLengthCfgInfoEntry
                MAX-ACCESS not-accessible
                STATUS current
                DESCRIPTION
                    "Description."
                ::= { hwCBQoSBehaviorObjects 25 }
    
            
    --  1.3.6.1.4.1.2011.5.25.32.1.1.2.25.1
            -- 1.3.6.1.4.1.2011.5.25.32.1.1.2.25.1
            hwCBQoSDenyPacketLengthCfgInfoEntry OBJECT-TYPE
                SYNTAX HwCBQoSDenyPacketLengthCfgInfoEntry
                MAX-ACCESS not-accessible
                STATUS current
                DESCRIPTION
                    "Description."
                INDEX { hwCBQoSBehaviorIndex }
                ::= { hwCBQoSDenyPacketLengthCfgInfoTable 1 }
    
            
            HwCBQoSDenyPacketLengthCfgInfoEntry ::=
                SEQUENCE { 
                    hwCBQoSDenyPacketLengthOptype
                        INTEGER,
                    hwCBQoSDenyPacketLengthMin
                        Integer32,
                    hwCBQoSDenyPacketLengthMax
                        Integer32,
                   hwCBQoSDenyPacketLength
                        Integer32,
                    hwCBQoSDenyPacketLengthRowStatus
                        RowStatus
                 }
    
    --  1.3.6.1.4.1.2011.5.25.32.1.1.2.25.1.1
            -- 1.3.6.1.4.1.2011.5.25.32.1.1.2.25.1.1
            hwCBQoSDenyPacketLengthOptype OBJECT-TYPE
                SYNTAX INTEGER
                    {
                    range(1),
                    eq(2),
                    gt(3),
                    lt(4)
                    }
                MAX-ACCESS read-create
                STATUS current
                DESCRIPTION
                    "Description."
                ::= { hwCBQoSDenyPacketLengthCfgInfoEntry 1 }
    
            
    --  1.3.6.1.4.1.2011.5.25.32.1.1.2.25.1.2
            -- 1.3.6.1.4.1.2011.5.25.32.1.1.2.25.1.2
            hwCBQoSDenyPacketLengthMin OBJECT-TYPE
                SYNTAX Integer32 (0..32767)
                MAX-ACCESS read-create
                STATUS current
                DESCRIPTION
                    "Description."
                ::= { hwCBQoSDenyPacketLengthCfgInfoEntry 2 }
    
            
    --  1.3.6.1.4.1.2011.5.25.32.1.1.2.25.1.3
            -- 1.3.6.1.4.1.2011.5.25.32.1.1.2.25.1.3
            hwCBQoSDenyPacketLengthMax OBJECT-TYPE
                SYNTAX Integer32 (0..32767)
                MAX-ACCESS read-create
                STATUS current
                DESCRIPTION
                    "Description."
                ::= { hwCBQoSDenyPacketLengthCfgInfoEntry 3 }
 
    --  1.3.6.1.4.1.2011.5.25.32.1.1.2.25.1.4
            -- 1.3.6.1.4.1.2011.5.25.32.1.1.2.25.1.4
            hwCBQoSDenyPacketLength OBJECT-TYPE
                SYNTAX Integer32 (0..32767)
                MAX-ACCESS read-create
                STATUS current
                DESCRIPTION
                    "Description."
                ::= { hwCBQoSDenyPacketLengthCfgInfoEntry 4 }   
            
    --  1.3.6.1.4.1.2011.5.25.32.1.1.2.25.1.50
            -- 1.3.6.1.4.1.2011.5.25.32.1.1.2.25.1.50
            hwCBQoSDenyPacketLengthRowStatus OBJECT-TYPE
                SYNTAX RowStatus
                MAX-ACCESS read-create
                STATUS current
                DESCRIPTION
                    "Description."
                ::= { hwCBQoSDenyPacketLengthCfgInfoEntry 50 }
    
            
            -- 1.3.6.1.4.1.2011.5.25.32.1.1.2.26
            hwCBQoSDAAStatisticsCfgInfoTable OBJECT-TYPE
                SYNTAX SEQUENCE OF HwCBQoSDAAStatisticsCfgInfoEntry
                MAX-ACCESS not-accessible
                STATUS current
                DESCRIPTION
                    "Description."
                ::= { hwCBQoSBehaviorObjects 26 }
    
            
            -- 1.3.6.1.4.1.2011.5.25.32.1.1.2.26.1
            hwCBQoSDAAStatisticsCfgInfoEntry OBJECT-TYPE
                SYNTAX HwCBQoSDAAStatisticsCfgInfoEntry
                MAX-ACCESS not-accessible
                STATUS current
                DESCRIPTION
                    "Description."
                INDEX { hwCBQoSBehaviorIndex }
                ::= { hwCBQoSDAAStatisticsCfgInfoTable 1 }
    
            
            HwCBQoSDAAStatisticsCfgInfoEntry ::=
                SEQUENCE { 
                    hwCBQoSDAAStatisticsSummary
                        INTEGER,
                    hwCBQoSDAAStatisticsRowStatus
                        RowStatus
                 }
    
            -- 1.3.6.1.4.1.2011.5.25.32.1.1.2.26.1.1
            hwCBQoSDAAStatisticsSummary OBJECT-TYPE
                SYNTAX INTEGER
                    {
                    enable(1),
                    disable(2)
                    }
                MAX-ACCESS read-create
                STATUS current
                DESCRIPTION
                    "Description."
                ::= { hwCBQoSDAAStatisticsCfgInfoEntry 1 }

        
        -- 1.3.6.1.4.1.2011.5.25.32.1.1.2.26.1.50
        hwCBQoSDAAStatisticsRowStatus OBJECT-TYPE
            SYNTAX RowStatus
            MAX-ACCESS read-create
            STATUS current
            DESCRIPTION
                "Description."
            ::= { hwCBQoSDAAStatisticsCfgInfoEntry 50 }

        
        -- 1.3.6.1.4.1.2011.5.25.32.1.1.2.27
        hwCBQoSDAATariffLevelCfgInfoTable OBJECT-TYPE
            SYNTAX SEQUENCE OF HwCBQoSDAATariffLevelCfgInfoEntry
            MAX-ACCESS not-accessible
            STATUS current
            DESCRIPTION
                "Description."
            ::= { hwCBQoSBehaviorObjects 27 }

        
        -- 1.3.6.1.4.1.2011.5.25.32.1.1.2.27.1
        hwCBQoSDAATariffLevelCfgInfoEntry OBJECT-TYPE
            SYNTAX HwCBQoSDAATariffLevelCfgInfoEntry
            MAX-ACCESS not-accessible
            STATUS current
            DESCRIPTION
                "Description."
            INDEX { hwCBQoSBehaviorIndex }
            ::= { hwCBQoSDAATariffLevelCfgInfoTable 1 }

        
        HwCBQoSDAATariffLevelCfgInfoEntry ::=
            SEQUENCE { 
                hwCBQoSDAATariffLevelValue
                    Integer32,
                hwCBQoSDAATariffLevelRowStatus
                    RowStatus
             }

        -- 1.3.6.1.4.1.2011.5.25.32.1.1.2.27.1.1
        hwCBQoSDAATariffLevelValue OBJECT-TYPE
            SYNTAX Integer32 (1..8)
            MAX-ACCESS read-create
            STATUS current
            DESCRIPTION
                "Description."
            ::= { hwCBQoSDAATariffLevelCfgInfoEntry 1 }


     -- 1.3.6.1.4.1.2011.5.25.32.1.1.2.27.1.50
        hwCBQoSDAATariffLevelRowStatus OBJECT-TYPE
             SYNTAX RowStatus
             MAX-ACCESS read-create
             STATUS current
             DESCRIPTION
                   "Description."
             ::= { hwCBQoSDAATariffLevelCfgInfoEntry 50 }

    --  RemarkIpDf behavior
        hwCBQoSRemarkIpDfCfgInfoTable OBJECT-TYPE
            SYNTAX SEQUENCE OF HwCBQoSRemarkIpDfCfgInfoEntry
            MAX-ACCESS not-accessible
            STATUS current
            DESCRIPTION
                "A table of Remark Ip-Df configuration information."
            ::= { hwCBQoSBehaviorObjects 28 }

        
        hwCBQoSRemarkIpDfCfgInfoEntry OBJECT-TYPE
            SYNTAX HwCBQoSRemarkIpDfCfgInfoEntry
            MAX-ACCESS not-accessible
            STATUS current
            DESCRIPTION
                "Remark Ip-Df Configuration Information Entry."
            INDEX { hwCBQoSBehaviorIndex }
            ::= { hwCBQoSRemarkIpDfCfgInfoTable 1 }

        
        HwCBQoSRemarkIpDfCfgInfoEntry ::=
            SEQUENCE { 
                hwCBQoSRemarkIpDf
                    Integer32,
                hwCBQoSRemarkIpDfRowStatus
                    RowStatus
             }

        
        hwCBQoSRemarkIpDf OBJECT-TYPE
            SYNTAX Integer32 (0..1)
            MAX-ACCESS read-create
            STATUS current
            DESCRIPTION
                "
                0: remark ip-df 0
                1: remark ip-df 1"
            ::= { hwCBQoSRemarkIpDfCfgInfoEntry 1 }

        
        hwCBQoSRemarkIpDfRowStatus OBJECT-TYPE
            SYNTAX RowStatus
            MAX-ACCESS read-create
            STATUS current
            DESCRIPTION
                "RowStatus. Three actions are used: active,
                createAndGo, destroy"
            ::= { hwCBQoSRemarkIpDfCfgInfoEntry 2 }  
            
            
 --  DropProfileCfg
        hwCBQoSDropProfileCfgInfoTable OBJECT-TYPE
            SYNTAX SEQUENCE OF HwCBQoSDropProfileCfgInfoEntry
            MAX-ACCESS not-accessible
            STATUS current
            DESCRIPTION
                "A table of drop profile configuration information."
            ::= { hwCBQoSBehaviorObjects 29 }

        
        hwCBQoSDropProfileCfgInfoEntry OBJECT-TYPE
            SYNTAX HwCBQoSDropProfileCfgInfoEntry
            MAX-ACCESS not-accessible
            STATUS current
            DESCRIPTION
                "Drop Profile Configuration Information Entry."
            INDEX { hwCBQoSDropProfileIndex }
            ::= { hwCBQoSDropProfileCfgInfoTable 1 }

        
        HwCBQoSDropProfileCfgInfoEntry ::=
            SEQUENCE { 
                hwCBQoSDropProfileIndex
                    Integer32,
                hwCBQoSDropProfileName
                    OCTET STRING,
                hwCBQoSDropProfileType
                    Integer32,
                hwCBQoSDropProfileRowStatus
                    RowStatus
             }

        hwCBQoSDropProfileIndex OBJECT-TYPE
            SYNTAX Integer32
            MAX-ACCESS read-only
            STATUS current
            DESCRIPTION
                "The value of this object identifies the index of the drop profile.
                 The value ranges from 1 to 31.
                 This object has no default value."
            ::= { hwCBQoSDropProfileCfgInfoEntry 1 }
        
        hwCBQoSDropProfileName OBJECT-TYPE
            SYNTAX OCTET STRING (SIZE (1..31))
            MAX-ACCESS read-create
            STATUS current
            DESCRIPTION
                "This object indicates the name of the drop profile.
                 The value of this object is a string of 1 to 31 visible ASCII characters, with no default value.
                 Space cannot exist between the characters in the string. The initial space and end space are ignored."
            ::= { hwCBQoSDropProfileCfgInfoEntry 2 }   
            
        hwCBQoSDropProfileType OBJECT-TYPE
            SYNTAX Integer32 (0..1)
            MAX-ACCESS read-create
            STATUS current
            DESCRIPTION
                "
                0: based on IP-precedence
                1: based on dscp
                The default value is 0"         
            DEFVAL { 0 }
            ::= { hwCBQoSDropProfileCfgInfoEntry 3 }
            
        hwCBQoSDropProfileRowStatus OBJECT-TYPE
            SYNTAX RowStatus
            MAX-ACCESS read-create
            STATUS current
            DESCRIPTION
                "This object indicates the row status.
                 The value of this object can be Active(1), CreateAndGo(4), or Destroy(6).
                 This object has no default value."
            ::= { hwCBQoSDropProfileCfgInfoEntry 4 }  
            
            
 --  DropProfileClass
        hwCBQoSDropProfileClassCfgInfoTable OBJECT-TYPE
            SYNTAX SEQUENCE OF HwCBQoSDropProfileClassCfgInfoEntry
            MAX-ACCESS not-accessible
            STATUS current
            DESCRIPTION
                "A table of drop profile class configuration information."
            ::= { hwCBQoSBehaviorObjects 30 }

        
        hwCBQoSDropProfileClassCfgInfoEntry OBJECT-TYPE
            SYNTAX HwCBQoSDropProfileClassCfgInfoEntry
            MAX-ACCESS not-accessible
            STATUS current
            DESCRIPTION
                "Drop Profile Class Configuration Information Entry."
            INDEX { hwCBQoSDropProfileIndex, hwCBQoSDropProfileClassValue }
            ::= { hwCBQoSDropProfileClassCfgInfoTable 1 }

        
        HwCBQoSDropProfileClassCfgInfoEntry ::=
            SEQUENCE { 
                hwCBQoSDropProfileClassValue
                    Integer32,
                hwCBQoSDropProfileLowLimit
                    Integer32,
                hwCBQoSDropProfileHighLimit
                    Integer32,
                hwCBQoSDropProfileDiscardProb
                    Integer32
             }

        hwCBQoSDropProfileClassValue OBJECT-TYPE
            SYNTAX Integer32 (0..63)
            MAX-ACCESS read-only
            STATUS current
            DESCRIPTION
                "The value of this object identifies the value of WRED based on the class.
                 IP precedence based WRED: the value ranges from 0 to 31. 
                 DSCP (DiffServ code points) based WRED: the value ranges from 0 to 63
                 This object has no default value."
            ::= { hwCBQoSDropProfileClassCfgInfoEntry 1 }
        
        hwCBQoSDropProfileLowLimit OBJECT-TYPE
            SYNTAX Integer32 (0..100)
            MAX-ACCESS read-write
            STATUS current
            DESCRIPTION
                "This object indicates the low limit for the WRED, the percent of the current queue length.
                 The range of the value is 0 to 100.
                 The default value is 30."   
            DEFVAL { 30 }
            ::= { hwCBQoSDropProfileClassCfgInfoEntry 2 }   
            
        hwCBQoSDropProfileHighLimit OBJECT-TYPE
            SYNTAX Integer32 (0..100)
            MAX-ACCESS read-write
            STATUS current
            DESCRIPTION
                "This object indicates the high limit for the WRED, the percent of the current queue length.
                 The range of the value is 0 to 100.
                 The default value is 100."
            DEFVAL { 100 }
            ::= { hwCBQoSDropProfileClassCfgInfoEntry 3 }
            
        hwCBQoSDropProfileDiscardProb OBJECT-TYPE
            SYNTAX Integer32 (0..100)
            MAX-ACCESS read-write
            STATUS current
            DESCRIPTION
                "This object indicates the discard probility for the WRED.
                 The range of the value is 0 to 100.
                 The default value is 10."
            DEFVAL { 10 }
            ::= { hwCBQoSDropProfileClassCfgInfoEntry 4 }                                             
 --  redirect vsi
 --  begin add by wangyonggui 00176838 for redirect vsi 2012-3-24
        hwCBQoSRedirectVsiTable OBJECT-TYPE
            SYNTAX SEQUENCE OF HwCBQoSRedirectVsiEntry
            MAX-ACCESS not-accessible
            STATUS current
            DESCRIPTION
                "A table of redirect vsi configuration information."
            ::= { hwCBQoSBehaviorObjects 31 }

        
        hwCBQoSRedirectVsiEntry OBJECT-TYPE
            SYNTAX HwCBQoSRedirectVsiEntry
            MAX-ACCESS not-accessible
            STATUS current
            DESCRIPTION
                "Drop Profile Class Configuration Information Entry."
            INDEX { hwCBQoSBehaviorIndex }
            ::= { hwCBQoSRedirectVsiTable 1 }

        
        HwCBQoSRedirectVsiEntry ::=
            SEQUENCE {         
                hwCBQoSRedirectVsiName
                    OCTET STRING,          
                hwCBQoSRedirectVsiRowStatus
                    RowStatus 
                     }

        hwCBQoSRedirectVsiName OBJECT-TYPE   
            SYNTAX OCTET STRING (SIZE (1..31))
            MAX-ACCESS read-create
            STATUS current
            DESCRIPTION
                "the vsi name of data flow redirected to."
            ::= { hwCBQoSRedirectVsiEntry 1 }   
        
        hwCBQoSRedirectVsiRowStatus OBJECT-TYPE
            SYNTAX RowStatus
            MAX-ACCESS read-create
            STATUS current
            DESCRIPTION
                "This object indicates the row status.
                The value of this object can be Active(1), CreateAndGo(4), or Destroy(6).
                This object has no default value.
                "
            ::= { hwCBQoSRedirectVsiEntry 2 }

 --  end add by wangyonggui 00176838 for redirect vsi 2012-3-24
 --  Suppression
 --  begin add by dengyunbo 00105021 for mqc Suppression 2012-11-06
        hwCBQoSSuppressionCfgInfoTable OBJECT-TYPE
            SYNTAX SEQUENCE OF HwCBQoSSuppressionCfgInfoEntry
            MAX-ACCESS not-accessible
            STATUS current
            DESCRIPTION
                "A table of mqc Suppression configuration information."
            ::= { hwCBQoSBehaviorObjects 32 }

        
        hwCBQoSSuppressionCfgInfoEntry OBJECT-TYPE
            SYNTAX HwCBQoSSuppressionCfgInfoEntry
            MAX-ACCESS not-accessible
            STATUS current
            DESCRIPTION
                "Mqc Suppression Configuration Information Entry."
            INDEX { hwCBQoSBehaviorIndex }
            ::= { hwCBQoSSuppressionCfgInfoTable 1 }

        
        HwCBQoSSuppressionCfgInfoEntry ::=
            SEQUENCE {         
                 hwCBQoSSuppressionType
                    INTEGER,
                 hwCBQoSSuppressionCir
                    Integer32, 
                 hwCBQoSSuppressionCbs
                    Integer32, 
                 hwCBQoSSuppressionGreenAction
                    CarAction, 
                 hwCBQoSSuppressionGreenRemarkValue
                    Integer32,
                 hwCBQoSSuppressionRedAction
                    CarAction, 
                 hwCBQoSSuppressionRedRemarkValue
                    Integer32,            
                 hwCBQoSSuppressionRowStatus
                    RowStatus 
                     }

        hwCBQoSSuppressionType OBJECT-TYPE
            SYNTAX INTEGER
                {
                broadcast(1),
                multicast(2),
                unkonwnunicast(3)
                }
            MAX-ACCESS read-only
            STATUS current
            DESCRIPTION
                "This object indicates the suppression type."
            ::= { hwCBQoSSuppressionCfgInfoEntry 1 }
            
        hwCBQoSSuppressionCir OBJECT-TYPE
            SYNTAX Integer32
            MAX-ACCESS read-create
            STATUS current
            DESCRIPTION
                "The value of this object identifies the Committed Information Rate (CIR).
                 The value ranges from 100 to 1000000, in kbit/s, with no default value.
                "
            ::= { hwCBQoSSuppressionCfgInfoEntry 2 }

        hwCBQoSSuppressionCbs OBJECT-TYPE
            SYNTAX Integer32
            MAX-ACCESS read-create
            STATUS current
            DESCRIPTION
                "The value of this object identifies the Committed Burst Size (CBS).
                 The value ranges from 10000 to 33554432 bytes.
                 The default value is 10000 bytes.
                "
            ::= { hwCBQoSSuppressionCfgInfoEntry 3 }

        hwCBQoSSuppressionGreenAction OBJECT-TYPE
            SYNTAX CarAction
            MAX-ACCESS read-create
            STATUS current
            DESCRIPTION
                "The value of this object identifies the action adopted when CIR is not reached.
                 pass (1),
                 discard (2),
                 The default value is pass (1).
                 "
            DEFVAL { pass }
            ::= { hwCBQoSSuppressionCfgInfoEntry 4 }

        hwCBQoSSuppressionGreenRemarkValue OBJECT-TYPE
            SYNTAX Integer32 (-1 | 11..81)
            MAX-ACCESS read-create
            STATUS current
            DESCRIPTION
                "The value is to remark When green action is remarking.
                the range is 11~81;   
                the high bit represents service-class,the range is 1~8 (1:be 2:af1 3:af2 4:af3 5:af4 6:ef 7:cs6 8:cs7)
                the low bit represents color,the range is 1~3 (1:green 2:yellow 3:red)
                Only software QoS support this node.
                -1 is returned only when getting value from hardware QoS or when action being pass,discard of software QoS.
                -1 can't be set."
            ::= { hwCBQoSSuppressionCfgInfoEntry 5 }
            
        hwCBQoSSuppressionRedAction OBJECT-TYPE
            SYNTAX CarAction
            MAX-ACCESS read-create
            STATUS current
            DESCRIPTION
                "The value of this object identifies the action performed when CIR is exceeded.
                 pass (1),
                 discard (2),
                 The default value is pass (1).
                 "
            DEFVAL { discard }
            ::= { hwCBQoSSuppressionCfgInfoEntry 6 }

        
        hwCBQoSSuppressionRedRemarkValue OBJECT-TYPE
            SYNTAX Integer32 (-1 | 11..81)
            MAX-ACCESS read-create
            STATUS current
            DESCRIPTION
                "The value is to remark When red action is remarking.
                For remarking DSCP, the range is 11~81; 
                the high bit represents service-class,the range is 1~8 (1:be 2:af1 3:af2 4:af3 5:af4 6:ef 7:cs6 8:cs7)
                the low bit represents color,the range is 1~3 (1:green 2:yellow 3:red)
                For remarking IP Precedence and MPLS EXP, the range is 0~7;
                Only software QoS support this node.
                -1 is returned only when getting value from hardware QoS or when action being pass,discard of software QoS.
                -1 can't be set."
            ::= { hwCBQoSSuppressionCfgInfoEntry 7 }
        
        hwCBQoSSuppressionRowStatus OBJECT-TYPE
            SYNTAX RowStatus
            MAX-ACCESS read-create
            STATUS current
            DESCRIPTION
                "This object indicates the row status.
                The value of this object can be Active(1), CreateAndGo(4), or Destroy(6).
                This object has no default value.
                "
            ::= { hwCBQoSSuppressionCfgInfoEntry 8 }

 --  end add by dengyunbo 00105021 for mqc Suppression 2012-11-06

-- hwCBQoSPolicyObjects
        hwCBQoSPolicyObjects OBJECT IDENTIFIER ::= { hwCBQoSObjects 3 }

        
--  Traffic Policy Next Index
        hwCBQoSPolicyIndexNext OBJECT-TYPE
            SYNTAX Integer32
            MAX-ACCESS read-only
            STATUS current
            DESCRIPTION
                "This object contains an appropriate value to be used for hwCBQoSPolicyIndex
                when creating rows in the hwCBQoSPolicyCfgInfoTable. Begin with 0."
            ::= { hwCBQoSPolicyObjects 1 }

        
--  Traffic Policy
        hwCBQoSPolicyCfgInfoTable OBJECT-TYPE
            SYNTAX SEQUENCE OF HwCBQoSPolicyCfgInfoEntry
            MAX-ACCESS not-accessible
            STATUS current
            DESCRIPTION
                "This table describes the detailed information about the QoS policy."
            ::= { hwCBQoSPolicyObjects 2 }

        
        hwCBQoSPolicyCfgInfoEntry OBJECT-TYPE
            SYNTAX HwCBQoSPolicyCfgInfoEntry
            MAX-ACCESS not-accessible
            STATUS current
            DESCRIPTION
                "Traffic Policy Configuration Information Entry."
            INDEX { hwCBQoSPolicyIndex }
            ::= { hwCBQoSPolicyCfgInfoTable 1 }

        
        HwCBQoSPolicyCfgInfoEntry ::=
            SEQUENCE { 
                hwCBQoSPolicyIndex
                    Integer32,
                hwCBQoSPolicyName
                    OCTET STRING,
                hwCBQoSPolicyClassCount
                    Integer32,
                hwCBQoSPolicyConfigMode
                    INTEGER,
                hwCBQoSPolicyRowStatus
                    RowStatus,
                hwCBQoSPolicyShareFlag
                    INTEGER,
                hwCBQoSPolicyStatisticsFlag
                    EnabledStatus
             }

        hwCBQoSPolicyIndex OBJECT-TYPE
            SYNTAX Integer32
            MAX-ACCESS read-only
            STATUS current
            DESCRIPTION
                "The value of this object identifies the policy index.
The value ranges from 1 to 1024.
This object has no default value.
"
            ::= { hwCBQoSPolicyCfgInfoEntry 1 }

        
        hwCBQoSPolicyName OBJECT-TYPE
            SYNTAX OCTET STRING (SIZE (1..64))
            MAX-ACCESS read-create
            STATUS current
            DESCRIPTION
                "This object indicates the policy name.
The value of this object is a string of 1 to 64 visible ASCII characters.
This object has no default value.
Space cannot exist between the characters in the string. The initial space and end space are ignored.
"
            ::= { hwCBQoSPolicyCfgInfoEntry 2 }

        
        hwCBQoSPolicyClassCount OBJECT-TYPE
            SYNTAX Integer32
            MAX-ACCESS read-only
            STATUS current
            DESCRIPTION
                "The value of this object identifies the number of traffic classes that are associated with a policy."
            ::= { hwCBQoSPolicyCfgInfoEntry 3 }

        
        hwCBQoSPolicyConfigMode OBJECT-TYPE
            SYNTAX INTEGER
                {
                unavailable(-1),
                config(1),
                auto(2)
                }
            MAX-ACCESS read-create
            STATUS current
            DESCRIPTION
                "Configuration mode of Traffic Policy.
                Only hardware QoS support this node.
                -1 is returned only when getting value from software QoS.
                -1 can't be set."
            DEFVAL { config }
            ::= { hwCBQoSPolicyCfgInfoEntry 4 }

        
        hwCBQoSPolicyRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSPolicyCfgInfoEntry 5 }

        
        hwCBQoSPolicyShareFlag OBJECT-TYPE
            SYNTAX INTEGER
                {
                multiple(1),
                single(2)
                }
            MAX-ACCESS read-create
            STATUS current
            DESCRIPTION
                "The value of the object identifies the attribute flag deciding sharing or not sharing a policy.
The value can be either of the following:
multiple(1): indicates that a policy is shared.
single(2): indicates that a policy is not shared.
The default value is multiple(1).
"
            DEFVAL { multiple }
            ::= { hwCBQoSPolicyCfgInfoEntry 6 }

        
        hwCBQoSPolicyStatisticsFlag OBJECT-TYPE
            SYNTAX EnabledStatus
            MAX-ACCESS read-create
            STATUS current
            DESCRIPTION
                "This object indicates the flag deciding whether the policy statistics are enabled.
The value of this object can be either of the following:
enabled(1) 
disabled(2) 
The default value is disabled (2).
"
            DEFVAL { disabled }
            ::= { hwCBQoSPolicyCfgInfoEntry 7 }

        
--  Classifier-Behavior in QoS policy
        hwCBQoSPolicyClassCfgInfoTable OBJECT-TYPE
            SYNTAX SEQUENCE OF HwCBQoSPolicyClassCfgInfoEntry
            MAX-ACCESS not-accessible
            STATUS current
            DESCRIPTION
                "A table of QoS Policy classifier-behavior configuration information."
            ::= { hwCBQoSPolicyObjects 3 }

        
        hwCBQoSPolicyClassCfgInfoEntry OBJECT-TYPE
            SYNTAX HwCBQoSPolicyClassCfgInfoEntry
            MAX-ACCESS not-accessible
            STATUS current
            DESCRIPTION
                "This table describes the association between the traffic class and traffic behavior in a QoS policy."
            INDEX { hwCBQoSPolicyIndex, hwCBQoSPolicyClassIndex }
            ::= { hwCBQoSPolicyClassCfgInfoTable 1 }

        
        HwCBQoSPolicyClassCfgInfoEntry ::=
            SEQUENCE { 
                hwCBQoSPolicyClassIndex
                    Integer32,
                hwCBQoSPolicyClassClassifierIndex
                    Integer32,
                hwCBQoSPolicyClassClassifierName
                    OCTET STRING,
                hwCBQoSPolicyClassBehaviorIndex
                    Integer32,
                hwCBQoSPolicyClassBehaviorName
                    OCTET STRING,
                hwCBQoSPolicyClassPrecedence
                    Integer32,
                hwCBQoSPolicyClassRowStatus
                    RowStatus
             }

        hwCBQoSPolicyClassIndex OBJECT-TYPE
            SYNTAX Integer32
            MAX-ACCESS read-only
            STATUS current
            DESCRIPTION
                "The value of the object identifies the policy class index in a QoS policy.
The value ranges from 0 to 255.
This object has no default value.
"
            ::= { hwCBQoSPolicyClassCfgInfoEntry 1 }

        
        hwCBQoSPolicyClassClassifierIndex OBJECT-TYPE
            SYNTAX Integer32
            MAX-ACCESS read-create
            STATUS current
            DESCRIPTION
                "The value of the object identifies the index of the classifier applied by a policy.
The value ranges from 0 to 4095.
This object has no default value.
"
            ::= { hwCBQoSPolicyClassCfgInfoEntry 2 }

        
        hwCBQoSPolicyClassClassifierName OBJECT-TYPE
            SYNTAX OCTET STRING (SIZE (1..64))
            MAX-ACCESS read-only
            STATUS current
            DESCRIPTION
                "This object indicates the policy class name in a QoS policy.
The value of this object is a string of 1 to 64 visible ASCII characters.
This object has no default value.
Space cannot exist between the characters in the string. The initial space and end space are ignored.
"
            ::= { hwCBQoSPolicyClassCfgInfoEntry 3 }

        
        hwCBQoSPolicyClassBehaviorIndex OBJECT-TYPE
            SYNTAX Integer32
            MAX-ACCESS read-create
            STATUS current
            DESCRIPTION
                "The value of the object identifies the index of the behavior applied by a policy.
The value ranges from 0 to 4095. 
"
            ::= { hwCBQoSPolicyClassCfgInfoEntry 4 }

        
        hwCBQoSPolicyClassBehaviorName OBJECT-TYPE
            SYNTAX OCTET STRING (SIZE (1..64))
            MAX-ACCESS read-only
            STATUS current
            DESCRIPTION
                "This object indicates the name of the behavior applied by a policy.
The value of this object is a string of 1 to 64 visible ASCII characters.
This object has no default value.
Space cannot exist between the characters in the string. The initial space and end space are ignored.
"
            ::= { hwCBQoSPolicyClassCfgInfoEntry 5 }

        
        hwCBQoSPolicyClassPrecedence OBJECT-TYPE
            SYNTAX Integer32 (-1 | 0..65535)
            MAX-ACCESS read-create
            STATUS current
            DESCRIPTION
                "The Precedence of the class in the policy.
                Only hardware QoS support this node.
                -1 is returned only when getting value from software QoS.
                -1 can't be set."
            ::= { hwCBQoSPolicyClassCfgInfoEntry 6 }

        
        hwCBQoSPolicyClassRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSPolicyClassCfgInfoEntry 7 }

        hwCBQoSPolicyShareModeCfgInfoTable OBJECT-TYPE
            SYNTAX SEQUENCE OF HwCBQoSPolicyShareModeCfgInfoEntry
            MAX-ACCESS not-accessible
            STATUS current
            DESCRIPTION
                "Policy Share Mode feature configuration information."
            ::= { hwCBQoSPolicyObjects 4 }
        
        hwCBQoSPolicyShareModeCfgInfoEntry OBJECT-TYPE
            SYNTAX HwCBQoSPolicyShareModeCfgInfoEntry
            MAX-ACCESS not-accessible
            STATUS current
            DESCRIPTION
                "Policy Share Mode feature configuration information Entry."
            INDEX { hwCBQoSPolicyIndex }
            ::= { hwCBQoSPolicyShareModeCfgInfoTable 1 }
        HwCBQoSPolicyShareModeCfgInfoEntry ::=
            SEQUENCE { 
                hwCBQoSPolicyShareModeFlag
                    EnabledStatus, 
                hwCBQoSPolicyShareModeRowStatus
                    RowStatus
             }
        hwCBQoSPolicyShareModeFlag OBJECT-TYPE
            SYNTAX EnabledStatus            
            MAX-ACCESS read-create
            STATUS current
            DESCRIPTION
                "The flag that the share Mode of a policy  is enabled."
            DEFVAL{enabled}
            ::= { hwCBQoSPolicyShareModeCfgInfoEntry 1 }  
        hwCBQoSPolicyShareModeRowStatus OBJECT-TYPE
            SYNTAX RowStatus 
            MAX-ACCESS read-create
            STATUS current
            DESCRIPTION
                "RowStatus. Three actions are used: active,
                createAndGo, destroy."
            ::= { hwCBQoSPolicyShareModeCfgInfoEntry 2 }                 
-- hwCBQoSApplyPolicyObjects
        hwCBQoSApplyPolicyObjects OBJECT IDENTIFIER ::= { hwCBQoSObjects 4 }

        
--  Policy Instance on interface Table
        hwCBQoSIfApplyPolicyTable OBJECT-TYPE
            SYNTAX SEQUENCE OF HwCBQoSIfApplyPolicyEntry
            MAX-ACCESS not-accessible
            STATUS current
            DESCRIPTION
                "This table describes the attributes of an interface on which a QoS policy is applied."
            ::= { hwCBQoSApplyPolicyObjects 1 }

        
        hwCBQoSIfApplyPolicyEntry OBJECT-TYPE
            SYNTAX HwCBQoSIfApplyPolicyEntry
            MAX-ACCESS not-accessible
            STATUS current
            DESCRIPTION
                "Policy applied on interface Configuration Information Entry."
            INDEX { hwCBQoSIfApplyPolicyIfIndex, hwCBQoSIfApplyPolicyDirection }
            ::= { hwCBQoSIfApplyPolicyTable 1 }

        
        HwCBQoSIfApplyPolicyEntry ::=
            SEQUENCE { 
                hwCBQoSIfApplyPolicyIfIndex
                    Integer32,
                hwCBQoSIfApplyPolicyDirection
                    DirectionType,
                hwCBQoSIfApplyPolicyName
                    OCTET STRING,
                hwCBQoSIfApplyPolicyRowStatus
                    RowStatus,
                hwCBQoSIfApplyPolicyLinkLayer
                    INTEGER    
             }

        hwCBQoSIfApplyPolicyIfIndex OBJECT-TYPE
            SYNTAX Integer32
            MAX-ACCESS read-only
            STATUS current
            DESCRIPTION
                "The value of this object identifies the index of the interface on which the policy is applied.
This object has no value range and default value. The interface must not be an interface of the MPU or a Layer 2 interface.
"
            ::= { hwCBQoSIfApplyPolicyEntry 1 }

        
        hwCBQoSIfApplyPolicyDirection OBJECT-TYPE
            SYNTAX DirectionType
            MAX-ACCESS read-only
            STATUS current
            DESCRIPTION
                "The value of this object identifies the direction in which a policy is applied.
The value can be inbound(1) or outbound(2).
This object has no default value.
"
            ::= { hwCBQoSIfApplyPolicyEntry 2 }

        
        hwCBQoSIfApplyPolicyName OBJECT-TYPE
            SYNTAX OCTET STRING (SIZE (1..64))
            MAX-ACCESS read-create
            STATUS current
            DESCRIPTION
                "This object indicates the policy name.
The value of this object is a string of 1 to 64 visible ASCII characters.
This object has no default value.
Space cannot exist between the characters in the string. The initial space and end space are ignored.
"
            ::= { hwCBQoSIfApplyPolicyEntry 3 }

        
        hwCBQoSIfApplyPolicyRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSIfApplyPolicyEntry 4 }     
-- add by l00241571 for mpls-layer            
        hwCBQoSIfApplyPolicyLinkLayer OBJECT-TYPE
            SYNTAX INTEGER
            {
                linklayer(1),
                alllayer(2),
                iplayer(3),
                mplslayer(4)
                 }
            MAX-ACCESS read-create
            STATUS current
            DESCRIPTION
                "This object indicates the forwarding layer for a policy to take effect.

The value can be link-layer(1), all-layer(2),  ip-layer(3), or mplslayer(4).

The default value is ip-layer(3) .
"     
            ::= { hwCBQoSIfApplyPolicyEntry 5 }
   

        
--  Policy Instance on ATM PVC Table
        hwCBQoSAtmPvcApplyPolicyTable OBJECT-TYPE
            SYNTAX SEQUENCE OF HwCBQoSAtmPvcApplyPolicyEntry
            MAX-ACCESS not-accessible
            STATUS current
            DESCRIPTION
                "A table of QoS policy instance."
            ::= { hwCBQoSApplyPolicyObjects 2 }

        
        hwCBQoSAtmPvcApplyPolicyEntry OBJECT-TYPE
            SYNTAX HwCBQoSAtmPvcApplyPolicyEntry
            MAX-ACCESS not-accessible
            STATUS current
            DESCRIPTION
                "Policy applied on ATM PVC Configuration Information Entry."
            INDEX { hwCBQoSAtmPvcApplyPolicyIfIndex, hwCBQoSAtmPvcApplyPolicyVPI, hwCBQoSAtmPvcApplyPolicyVCI, hwCBQoSAtmPvcApplyPolicyDirection }
            ::= { hwCBQoSAtmPvcApplyPolicyTable 1 }

        
        HwCBQoSAtmPvcApplyPolicyEntry ::=
            SEQUENCE { 
                hwCBQoSAtmPvcApplyPolicyIfIndex
                    Integer32,
                hwCBQoSAtmPvcApplyPolicyVPI
                    Integer32,
                hwCBQoSAtmPvcApplyPolicyVCI
                    Integer32,
                hwCBQoSAtmPvcApplyPolicyDirection
                    DirectionType,
                hwCBQoSAtmPvcApplyPolicyName
                    OCTET STRING,
                hwCBQoSAtmPvcApplyPolicyRowStatus
                    RowStatus
             }

        hwCBQoSAtmPvcApplyPolicyIfIndex OBJECT-TYPE
            SYNTAX Integer32
            MAX-ACCESS read-only
            STATUS current
            DESCRIPTION
                "ATM Interface Index, equal to ifIndex."
            ::= { hwCBQoSAtmPvcApplyPolicyEntry 1 }

        
        hwCBQoSAtmPvcApplyPolicyVPI OBJECT-TYPE
            SYNTAX Integer32
            MAX-ACCESS read-only
            STATUS current
            DESCRIPTION
                "VPI value of ATM Interface."
            ::= { hwCBQoSAtmPvcApplyPolicyEntry 2 }

        
        hwCBQoSAtmPvcApplyPolicyVCI OBJECT-TYPE
            SYNTAX Integer32
            MAX-ACCESS read-only
            STATUS current
            DESCRIPTION
                "VCI value of ATM Interface."
            ::= { hwCBQoSAtmPvcApplyPolicyEntry 3 }

        
        hwCBQoSAtmPvcApplyPolicyDirection OBJECT-TYPE
            SYNTAX DirectionType
            MAX-ACCESS read-only
            STATUS current
            DESCRIPTION
                "Policy direction:
                inbound (1)
                outbound (2)"
            ::= { hwCBQoSAtmPvcApplyPolicyEntry 4 }

        
        hwCBQoSAtmPvcApplyPolicyName OBJECT-TYPE
            SYNTAX OCTET STRING (SIZE (1..31))
            MAX-ACCESS read-create
            STATUS current
            DESCRIPTION
                "Name of Traffic Policy."
            ::= { hwCBQoSAtmPvcApplyPolicyEntry 5 }

        
        hwCBQoSAtmPvcApplyPolicyRowStatus OBJECT-TYPE
            SYNTAX RowStatus
            MAX-ACCESS read-create
            STATUS current
            DESCRIPTION
                "RowStatus. Three actions are used: active,
                createAndGo, destroy"
            ::= { hwCBQoSAtmPvcApplyPolicyEntry 6 }

        
--  Policy Instance on vlanid Table
        hwCBQoSIfVlanApplyPolicyTable OBJECT-TYPE
            SYNTAX SEQUENCE OF HwCBQoSIfVlanApplyPolicyEntry
            MAX-ACCESS not-accessible
            STATUS current
            DESCRIPTION
                "This table is used to display information about traffic policies applied to VLAN packets."
            ::= { hwCBQoSApplyPolicyObjects 3 }

        
        hwCBQoSIfVlanApplyPolicyEntry OBJECT-TYPE
            SYNTAX HwCBQoSIfVlanApplyPolicyEntry
            MAX-ACCESS not-accessible
            STATUS current
            DESCRIPTION
                "Policy applied on Ethernet Vlan Configuration Information Entry."
            INDEX { hwCBQoSIfVlanApplyPolicyIfIndex, hwCBQoSIfVlanApplyPolicyDirection,  hwCBQoSIfVlanApplyPolicyVlanid1, hwCBQoSIfVlanApplyPolicyVlanid2}
            ::= { hwCBQoSIfVlanApplyPolicyTable 1 }

        
        HwCBQoSIfVlanApplyPolicyEntry ::=
            SEQUENCE { 
                hwCBQoSIfVlanApplyPolicyIfIndex
                    Integer32,   
                hwCBQoSIfVlanApplyPolicyDirection
                    DirectionType,
                hwCBQoSIfVlanApplyPolicyVlanid1
                    Integer32,
                hwCBQoSIfVlanApplyPolicyVlanid2
                    Integer32,   
                hwCBQoSIfVlanApplyPolicyCeVidEnd
                    Integer32, 
                hwCBQoSIfVlanApplyPolicyName
                    OCTET STRING,
                hwCBQoSIfVlanApplyPolicyRowStatus
                    RowStatus,
                hwCBQoSIfVlanApplyPolicyLinkLayer
                    INTEGER    
             }

        hwCBQoSIfVlanApplyPolicyIfIndex OBJECT-TYPE
            SYNTAX Integer32
            MAX-ACCESS read-only
            STATUS current
            DESCRIPTION
                "Indicates the Ethernet interface index."
            ::= { hwCBQoSIfVlanApplyPolicyEntry 1 }   
            
        hwCBQoSIfVlanApplyPolicyDirection OBJECT-TYPE
            SYNTAX DirectionType
            MAX-ACCESS read-only
            STATUS current
            DESCRIPTION
                "Indicates the direction to which the policy is applied."
            ::= { hwCBQoSIfVlanApplyPolicyEntry 2 }
     
        hwCBQoSIfVlanApplyPolicyVlanid1 OBJECT-TYPE
            SYNTAX Integer32
            MAX-ACCESS read-only
            STATUS current
            DESCRIPTION
                "PE VID of a traffic policy on a Layer 2 interface."
            ::= { hwCBQoSIfVlanApplyPolicyEntry 3 }

        
        hwCBQoSIfVlanApplyPolicyVlanid2 OBJECT-TYPE
            SYNTAX Integer32
            MAX-ACCESS read-create
            STATUS current
            DESCRIPTION
                "Start VLAN ID or CE VID of a traffic policy on a Layer 2 interface."
            ::= { hwCBQoSIfVlanApplyPolicyEntry 4 }
                
        hwCBQoSIfVlanApplyPolicyCeVidEnd OBJECT-TYPE
            SYNTAX Integer32
            MAX-ACCESS read-create
            STATUS current
            DESCRIPTION
                "End VLAN ID or CE VID of a traffic policy on a Layer 2 interface."
            ::= { hwCBQoSIfVlanApplyPolicyEntry 5 }

        
        hwCBQoSIfVlanApplyPolicyName OBJECT-TYPE
            SYNTAX OCTET STRING (SIZE (1..64))
            MAX-ACCESS read-create
            STATUS current
            DESCRIPTION
                "Indicates the policy name."
            ::= { hwCBQoSIfVlanApplyPolicyEntry 6 }

        
        hwCBQoSIfVlanApplyPolicyRowStatus OBJECT-TYPE
            SYNTAX RowStatus
            MAX-ACCESS read-create
            STATUS current
            DESCRIPTION
                "RowStatus. Three actions are used: active,
                createAndGo, destroy"
            ::= { hwCBQoSIfVlanApplyPolicyEntry 7 }   
 --modify by l00241571 for mpls-layer           
        hwCBQoSIfVlanApplyPolicyLinkLayer OBJECT-TYPE
            SYNTAX INTEGER
            {
                linklayer(1),
                alllayer(2),
                iplayer(3),
                mplslayer(4)
               }
            MAX-ACCESS read-create
            STATUS current
            DESCRIPTION
                "Indicates the link layer. The value range is: link-layer(1),all-layer(2),ip-layer(3),mpls-layer(4). "     

            ::= { hwCBQoSIfVlanApplyPolicyEntry 8 }
     

        
--  Policy Instance on fr class Table
        hwCBQoSFrClassApplyPolicyTable OBJECT-TYPE
            SYNTAX SEQUENCE OF HwCBQoSFrClassApplyPolicyEntry
            MAX-ACCESS not-accessible
            STATUS current
            DESCRIPTION
                "A table of QoS policy instance."
            ::= { hwCBQoSApplyPolicyObjects 4 }

        
        hwCBQoSFrClassApplyPolicyEntry OBJECT-TYPE
            SYNTAX HwCBQoSFrClassApplyPolicyEntry
            MAX-ACCESS not-accessible
            STATUS current
            DESCRIPTION
                "Policy applied on fr class Configuration Information Entry."
            INDEX { hwCBQoSFrClassApplyPolicyFrClassName, hwCBQoSFrClassApplyPolicyDirection }
            ::= { hwCBQoSFrClassApplyPolicyTable 1 }

        
        HwCBQoSFrClassApplyPolicyEntry ::=
            SEQUENCE { 
                hwCBQoSFrClassApplyPolicyFrClassName
                    OCTET STRING,
                hwCBQoSFrClassApplyPolicyDirection
                    DirectionType,
                hwCBQoSFrClassApplyPolicyName
                    OCTET STRING,
                hwCBQoSFrClassApplyPolicyRowStatus
                    RowStatus
             }

        hwCBQoSFrClassApplyPolicyFrClassName OBJECT-TYPE
            SYNTAX OCTET STRING (SIZE (1..31))
            MAX-ACCESS read-only
            STATUS current
            DESCRIPTION
                "The name of fr class."
            ::= { hwCBQoSFrClassApplyPolicyEntry 1 }

        
        hwCBQoSFrClassApplyPolicyDirection OBJECT-TYPE
            SYNTAX DirectionType
            MAX-ACCESS read-only
            STATUS current
            DESCRIPTION
                "Policy direction:
                inbound (1)
                outbound (2)"
            ::= { hwCBQoSFrClassApplyPolicyEntry 2 }

        
        hwCBQoSFrClassApplyPolicyName OBJECT-TYPE
            SYNTAX OCTET STRING (SIZE (1..31))
            MAX-ACCESS read-create
            STATUS current
            DESCRIPTION
                "Name of Traffic Policy."
            ::= { hwCBQoSFrClassApplyPolicyEntry 3 }

        
        hwCBQoSFrClassApplyPolicyRowStatus OBJECT-TYPE
            SYNTAX RowStatus
            MAX-ACCESS read-create
            STATUS current
            DESCRIPTION
                "RowStatus. Three actions are used: active,
                createAndGo, destroy"
            ::= { hwCBQoSFrClassApplyPolicyEntry 4 }

        
--  Policy Instance on fr pvc Table
        hwCBQoSFrPvcApplyPolicyTable OBJECT-TYPE
            SYNTAX SEQUENCE OF HwCBQoSFrPvcApplyPolicyEntry
            MAX-ACCESS not-accessible
            STATUS current
            DESCRIPTION
                "A table of QoS policy instance."
            ::= { hwCBQoSApplyPolicyObjects 5 }

        
        hwCBQoSFrPvcApplyPolicyEntry OBJECT-TYPE
            SYNTAX HwCBQoSFrPvcApplyPolicyEntry
            MAX-ACCESS not-accessible
            STATUS current
            DESCRIPTION
                "Policy applied on FR PVC Configuration Information Entry."
            INDEX { hwCBQoSFrPvcApplyPolicyIfIndex, hwCBQoSFrPvcApplyPolicyDlciNum, hwCBQoSFrPvcApplyPolicyDirection }
            ::= { hwCBQoSFrPvcApplyPolicyTable 1 }

        
        HwCBQoSFrPvcApplyPolicyEntry ::=
            SEQUENCE { 
                hwCBQoSFrPvcApplyPolicyIfIndex
                    Integer32,
                hwCBQoSFrPvcApplyPolicyDlciNum
                    Integer32,
                hwCBQoSFrPvcApplyPolicyDirection
                    DirectionType,
                hwCBQoSFrPvcApplyPolicyName
                    OCTET STRING
             }

        hwCBQoSFrPvcApplyPolicyIfIndex OBJECT-TYPE
            SYNTAX Integer32
            MAX-ACCESS read-only
            STATUS current
            DESCRIPTION
                "Fr Interface Index, equal to ifIndex."
            ::= { hwCBQoSFrPvcApplyPolicyEntry 1 }

        
        hwCBQoSFrPvcApplyPolicyDlciNum OBJECT-TYPE
            SYNTAX Integer32 (16..1007)
            MAX-ACCESS read-only
            STATUS current
            DESCRIPTION
                "Fr DLCI number."
            ::= { hwCBQoSFrPvcApplyPolicyEntry 2 }

        
        hwCBQoSFrPvcApplyPolicyDirection OBJECT-TYPE
            SYNTAX DirectionType
            MAX-ACCESS read-only
            STATUS current
            DESCRIPTION
                "Policy direction:
                inbound (1)
                outbound (2)"
            ::= { hwCBQoSFrPvcApplyPolicyEntry 3 }

        
        hwCBQoSFrPvcApplyPolicyName OBJECT-TYPE
            SYNTAX OCTET STRING (SIZE (1..31))
            MAX-ACCESS read-only
            STATUS current
            DESCRIPTION
                "Name of Traffic Policy."
            ::= { hwCBQoSFrPvcApplyPolicyEntry 4 }

        
--  Policy Instance on vsi Table
        hwCBQoSVsiApplyPolicyTable OBJECT-TYPE
            SYNTAX SEQUENCE OF HwCBQoSVsiApplyPolicyEntry
            MAX-ACCESS not-accessible
            STATUS current
            DESCRIPTION
                "A table of QoS policy instance."
            ::= { hwCBQoSApplyPolicyObjects 6 }

        
        hwCBQoSVsiApplyPolicyEntry OBJECT-TYPE
            SYNTAX HwCBQoSVsiApplyPolicyEntry
            MAX-ACCESS not-accessible
            STATUS current
            DESCRIPTION
                "Policy applied on VSI Configuration Information Entry."
            INDEX { hwCBQoSVsiApplyPolicyVsiIndex, hwCBQoSVsiApplyPolicyDirection }
            ::= { hwCBQoSVsiApplyPolicyTable 1 }

        
        HwCBQoSVsiApplyPolicyEntry ::=
            SEQUENCE { 
                hwCBQoSVsiApplyPolicyVsiIndex
                    Integer32,
                hwCBQoSVsiName
                    OCTET STRING,
                hwCBQoSVsiApplyPolicyDirection
                    DirectionType,
                hwCBQoSVsiApplyPolicyName
                    OCTET STRING,
                hwCBQoSVsiApplyPolicyRowStatus
                    RowStatus
             }

        hwCBQoSVsiApplyPolicyVsiIndex OBJECT-TYPE
            SYNTAX Integer32
            MAX-ACCESS read-only
            STATUS current
            DESCRIPTION
                "VSI Interface Index, equal to ifIndex."
            ::= { hwCBQoSVsiApplyPolicyEntry 1 }

        
        hwCBQoSVsiName OBJECT-TYPE
            SYNTAX OCTET STRING (SIZE (1..31))
            MAX-ACCESS read-create
            STATUS current
            DESCRIPTION
                "Vlan of Ethernet Interface."
            ::= { hwCBQoSVsiApplyPolicyEntry 2 }

        
        hwCBQoSVsiApplyPolicyDirection OBJECT-TYPE
            SYNTAX DirectionType
            MAX-ACCESS read-only
            STATUS current
            DESCRIPTION
                "Policy direction:
                inbound (1)
                outbound (2)"
            ::= { hwCBQoSVsiApplyPolicyEntry 3 }

        
        hwCBQoSVsiApplyPolicyName OBJECT-TYPE
            SYNTAX OCTET STRING (SIZE (1..31))
            MAX-ACCESS read-create
            STATUS current
            DESCRIPTION
                "Name of Traffic Policy."
            ::= { hwCBQoSVsiApplyPolicyEntry 4 }

        
        hwCBQoSVsiApplyPolicyRowStatus OBJECT-TYPE
            SYNTAX RowStatus
            MAX-ACCESS read-create
            STATUS current
            DESCRIPTION
                "RowStatus. Three actions are used: active,
                createAndGo, destroy"
            ::= { hwCBQoSVsiApplyPolicyEntry 5 }

        
                hwCBQoSVlanApplyPolicyTable OBJECT-TYPE
                        SYNTAX SEQUENCE OF HwCBQoSVlanApplyPolicyEntry
                        MAX-ACCESS not-accessible
                        STATUS current
                        DESCRIPTION
                                "A table of applying policy on VLAN."
                        ::= { hwCBQoSApplyPolicyObjects 7 }

                
                hwCBQoSVlanApplyPolicyEntry OBJECT-TYPE
                        SYNTAX HwCBQoSVlanApplyPolicyEntry
                        MAX-ACCESS not-accessible
                        STATUS current
                        DESCRIPTION
                                "Policy applied on VLAN Configuration Information Entry."
                        INDEX { hwCBQoSVlanApplyPolicyVlanId,hwCBQoSVlanApplyPolicyDirection }
                        ::= { hwCBQoSVlanApplyPolicyTable 1 }

                
                HwCBQoSVlanApplyPolicyEntry ::=
                        SEQUENCE 
                        { 
                            hwCBQoSVlanApplyPolicyVlanId
                                    Integer32,
                            hwCBQoSVlanApplyPolicyDirection
                                    INTEGER,
                            hwCBQoSVlanApplyPolicyName
                                    OCTET STRING,
                            hwCBQoSVlanApplyPolicyRowStatus
                                    RowStatus
                         }

                hwCBQoSVlanApplyPolicyVlanId OBJECT-TYPE
                        SYNTAX Integer32 (1..4094)
                        MAX-ACCESS read-only
                        STATUS current
                        DESCRIPTION
                                "VLAN number."
                        ::= { hwCBQoSVlanApplyPolicyEntry 1 }

                
                hwCBQoSVlanApplyPolicyDirection OBJECT-TYPE
                        SYNTAX INTEGER
                        {
                            inbound(1),
                            outbound(2)
                        }
                        MAX-ACCESS read-only
                        STATUS current
                        DESCRIPTION
                                "Policy Direction:
                                 inbound(1), apply policy inbound;
                                 outbound(2), apply policy outbound."
                        ::= { hwCBQoSVlanApplyPolicyEntry 2 }

                
                hwCBQoSVlanApplyPolicyName OBJECT-TYPE
                        SYNTAX OCTET STRING (SIZE (1..64))
                        MAX-ACCESS read-create
                        STATUS current
                        DESCRIPTION
                                "Policy name: The name of the applied policy."
                        ::= { hwCBQoSVlanApplyPolicyEntry 3 }

                
                hwCBQoSVlanApplyPolicyRowStatus OBJECT-TYPE
                        SYNTAX RowStatus
                        MAX-ACCESS read-create
                        STATUS current
                        DESCRIPTION
                                "RowStatus. Three actions are used: active, createAndGo, destroy."
                        ::= { hwCBQoSVlanApplyPolicyEntry 4 }
                        
        --beg: mod by j00126783 for policy-alarm
          hwCBQoSRuleNotSupportAlarmTable OBJECT-TYPE
                        SYNTAX SEQUENCE OF HwCBQoSRuleNotSupportAlarmEntry
                        MAX-ACCESS not-accessible
                        STATUS current
                        DESCRIPTION
                                "hwCBQoSRuleNotSupportAlarmTable"
                        ::= { hwCBQoSApplyPolicyObjects 8 }
                        
              hwCBQoSRuleNotSupportAlarmEntry OBJECT-TYPE
            SYNTAX HwCBQoSRuleNotSupportAlarmEntry
            MAX-ACCESS not-accessible
            STATUS current
            DESCRIPTION
                "hwCBQoSRuleNotSupportAlarmEntry"
            INDEX { hwCBQoSRuleDirection, hwCBQoSRuleSlotID, hwCBQoSRuleInfo }
            ::= { hwCBQoSRuleNotSupportAlarmTable 1 }
            
              HwCBQoSRuleNotSupportAlarmEntry ::=
            SEQUENCE { 
                  hwCBQoSRuleDirection
                    OCTET STRING,
                  hwCBQoSRuleSlotID      
                        Integer32,
                  hwCBQoSRuleInfo
                        OCTET STRING
                 }
                 
                    hwCBQoSRuleDirection OBJECT-TYPE
                    SYNTAX OCTET STRING (SIZE (1..31))
                MAX-ACCESS read-only
                STATUS current
                DESCRIPTION
                "hwCBQoSRuleDirection"
                 ::= { hwCBQoSRuleNotSupportAlarmEntry 1 }
                 
            hwCBQoSRuleSlotID OBJECT-TYPE
                    SYNTAX Integer32 (1..128)
                MAX-ACCESS read-only
                STATUS current
                DESCRIPTION
                "hwCBQoSRuleSlotID"
                 ::= { hwCBQoSRuleNotSupportAlarmEntry 2 }   
                   
            hwCBQoSRuleInfo OBJECT-TYPE
                    SYNTAX OCTET STRING (SIZE (1..511))
                MAX-ACCESS read-only
                STATUS current
                DESCRIPTION
                "hwCBQoSRuleInfo"
                 ::= { hwCBQoSRuleNotSupportAlarmEntry 3 }
       
       hwCBQoSActionNotSupportAlarmTable OBJECT-TYPE
                        SYNTAX SEQUENCE OF HwCBQoSActionNotSupportAlarmEntry
                        MAX-ACCESS not-accessible
                        STATUS current
                        DESCRIPTION
                                "hwCBQoSActionNotSupportAlarmTable"
                        ::= { hwCBQoSApplyPolicyObjects 9 }
                        
              hwCBQoSActionNotSupportAlarmEntry OBJECT-TYPE
            SYNTAX HwCBQoSActionNotSupportAlarmEntry
            MAX-ACCESS not-accessible
            STATUS current
            DESCRIPTION
                "hwCBQoSActionNotSupportAlarmEntry"
            INDEX { hwCBQoSActionDirection, hwCBQoSActionSlotID, hwCBQoSActionInfo }
            ::= { hwCBQoSActionNotSupportAlarmTable 1 }
            
              HwCBQoSActionNotSupportAlarmEntry ::=
            SEQUENCE { 
                  hwCBQoSActionDirection
                    OCTET STRING,
                  hwCBQoSActionSlotID      
                        Integer32,
                  hwCBQoSActionInfo
                        OCTET STRING
                 }
                 
                    hwCBQoSActionDirection OBJECT-TYPE
                    SYNTAX OCTET STRING (SIZE (1..31))
                MAX-ACCESS read-only
                STATUS current
                DESCRIPTION
                "hwCBQoSActionDirection"
                 ::= { hwCBQoSActionNotSupportAlarmEntry 1 }
                 
            hwCBQoSActionSlotID OBJECT-TYPE
                    SYNTAX Integer32 (1..128)
                MAX-ACCESS read-only
                STATUS current
                DESCRIPTION
                "hwCBQoSActionSlotID"
                 ::= { hwCBQoSActionNotSupportAlarmEntry 2 }     
            hwCBQoSActionInfo OBJECT-TYPE
                    SYNTAX OCTET STRING (SIZE (1..511))
                MAX-ACCESS read-only
                STATUS current
                DESCRIPTION
                "hwCBQoSActionInfo"
                 ::= { hwCBQoSActionNotSupportAlarmEntry 3 }                  
        --end: mod by j00126783 for policy-alarm                        

	-- multi-policy Instance on interface Table
        hwCBQoSIfApplyMultiPolicyTable OBJECT-TYPE
            SYNTAX SEQUENCE OF HwCBQoSIfApplyMultiPolicyEntry
            MAX-ACCESS not-accessible
            STATUS current
            DESCRIPTION
                "A table of applying multi-policy on interface."
            ::= { hwCBQoSApplyPolicyObjects 10 }

        
        hwCBQoSIfApplyMultiPolicyEntry OBJECT-TYPE
            SYNTAX HwCBQoSIfApplyMultiPolicyEntry
            MAX-ACCESS not-accessible
            STATUS current
            DESCRIPTION
                "Policy applied on interface Configuration Information Entry."
            INDEX { hwCBQoSIfApplyMultiPolicyIfIndex, hwCBQoSIfApplyMultiPolicyDirection, hwCBQoSIfApplyMultiPolicyIndex }
            ::= { hwCBQoSIfApplyMultiPolicyTable 1 }

        
        HwCBQoSIfApplyMultiPolicyEntry ::=
            SEQUENCE { 
                hwCBQoSIfApplyMultiPolicyIfIndex
                    Integer32,
                hwCBQoSIfApplyMultiPolicyDirection
                    DirectionType, 
                hwCBQoSIfApplyMultiPolicyIndex
                    Integer32,
                hwCBQoSIfApplyMultiPolicyName
                    OCTET STRING,
                hwCBQoSIfApplyMultiPolicyRowStatus
                    RowStatus
             }

        hwCBQoSIfApplyMultiPolicyIfIndex OBJECT-TYPE
            SYNTAX Integer32
            MAX-ACCESS read-only
            STATUS current
            DESCRIPTION
                "The value of this object identifies the index of the interface on which the policy is applied.
This object has no value range and default value. 
"
            ::= { hwCBQoSIfApplyMultiPolicyEntry 1 }

        
        hwCBQoSIfApplyMultiPolicyDirection OBJECT-TYPE
            SYNTAX DirectionType
            MAX-ACCESS read-only
            STATUS current
            DESCRIPTION
                "Policy Direction:
                 inbound(1), apply policy inbound;
                 outbound(2), apply policy outbound."
            ::= { hwCBQoSIfApplyMultiPolicyEntry 2 }

        hwCBQoSIfApplyMultiPolicyIndex OBJECT-TYPE
            SYNTAX Integer32
            MAX-ACCESS read-only
            STATUS current
            DESCRIPTION
                "The value of this object identifies the policy index.
"
            ::= { hwCBQoSIfApplyMultiPolicyEntry 3 }
         
        hwCBQoSIfApplyMultiPolicyName OBJECT-TYPE
            SYNTAX OCTET STRING (SIZE (1..31))
            MAX-ACCESS read-only
            STATUS current
            DESCRIPTION
                "Name of the applied policy."
            ::= { hwCBQoSIfApplyMultiPolicyEntry 4 }

        
        hwCBQoSIfApplyMultiPolicyRowStatus OBJECT-TYPE
            SYNTAX RowStatus
            MAX-ACCESS read-create
            STATUS current
            DESCRIPTION
                "This object indicates the row status.
The value of this object can be Active(1), CreateAndGo(4), or Destroy(6).
This object has no default value.
"
            ::= { hwCBQoSIfApplyMultiPolicyEntry 5 }     

-- multi-policy applied on vlan
		  hwCBQoSVlanApplyMultiPolicyTable OBJECT-TYPE
                        SYNTAX SEQUENCE OF HwCBQoSVlanApplyMultiPolicyEntry
                        MAX-ACCESS not-accessible
                        STATUS current
                        DESCRIPTION
                                "A table of applying multi-policy on VLAN."
                        ::= { hwCBQoSApplyPolicyObjects 11 }

                
                hwCBQoSVlanApplyMultiPolicyEntry OBJECT-TYPE
                        SYNTAX HwCBQoSVlanApplyMultiPolicyEntry
                        MAX-ACCESS not-accessible
                        STATUS current
                        DESCRIPTION
                                "Policy applied on VLAN Configuration Information Entry."
                        INDEX { hwCBQoSVlanApplyMultiPolicyVlanId, hwCBQoSVlanApplyMultiPolicyDirection, hwCBQoSVlanApplyMultiPolicyIndex}
                        ::= { hwCBQoSVlanApplyMultiPolicyTable 1 }

                
                HwCBQoSVlanApplyMultiPolicyEntry ::=
                        SEQUENCE 
                        { 
                            hwCBQoSVlanApplyMultiPolicyVlanId
                                    Integer32,
                            hwCBQoSVlanApplyMultiPolicyDirection
                                    INTEGER,
	          hwCBQoSVlanApplyMultiPolicyIndex
                                    Integer32,
                            hwCBQoSVlanApplyMultiPolicyName
                                    OCTET STRING,
                            hwCBQoSVlanApplyMultiPolicyRowStatus
                                    RowStatus
                         }

                hwCBQoSVlanApplyMultiPolicyVlanId OBJECT-TYPE
                        SYNTAX Integer32 (1..4094)
                        MAX-ACCESS read-only
                        STATUS current
                        DESCRIPTION
                                "VLAN number."
                        ::= { hwCBQoSVlanApplyMultiPolicyEntry 1 }

                
                hwCBQoSVlanApplyMultiPolicyDirection OBJECT-TYPE
                        SYNTAX INTEGER
                        {
                            inbound(1),
                            outbound(2)
                        }
                        MAX-ACCESS read-only
                        STATUS current
                        DESCRIPTION
                                "Policy Direction:
                                 inbound(1), apply policy inbound;
                                 outbound(2), apply policy outbound."
                        ::= { hwCBQoSVlanApplyMultiPolicyEntry 2 }

                hwCBQoSVlanApplyMultiPolicyIndex OBJECT-TYPE
	       SYNTAX Integer32
	       MAX-ACCESS read-only
	       STATUS current
	       DESCRIPTION
		"The value of this object identifies the policy index."
                        ::= { hwCBQoSVlanApplyMultiPolicyEntry 3 }
                
                hwCBQoSVlanApplyMultiPolicyName OBJECT-TYPE
                        SYNTAX OCTET STRING (SIZE (1..31))
                        MAX-ACCESS read-only
                        STATUS current
                        DESCRIPTION
                                "Name of the applied policy."
                        ::= { hwCBQoSVlanApplyMultiPolicyEntry 4 }

                
                hwCBQoSVlanApplyMultiPolicyRowStatus OBJECT-TYPE
                        SYNTAX RowStatus
                        MAX-ACCESS read-create
                        STATUS current
                        DESCRIPTION
                                "RowStatus. Three actions are used: active, createAndGo, destroy."
                        ::= { hwCBQoSVlanApplyMultiPolicyEntry 5 }

		--add by zhangyong 00291234
                hwCBQoSGlobalAclNotSupportAlarmTable OBJECT-TYPE
                        SYNTAX SEQUENCE OF HwCBQoSGlobalAclNotSupportAlarmEntry
                        MAX-ACCESS not-accessible
                        STATUS current
                        DESCRIPTION
                                "hwCBQoSGlobalAclNotSupportAlarmTable"
                        ::= { hwCBQoSApplyPolicyObjects 12 }
                        
              hwCBQoSGlobalAclNotSupportAlarmEntry OBJECT-TYPE
            SYNTAX HwCBQoSGlobalAclNotSupportAlarmEntry
            MAX-ACCESS not-accessible
            STATUS current
            DESCRIPTION
                "hwCBQoSGlobalAclNotSupportAlarmEntry"
            INDEX { hwCBQoSGlobalAclDirection, hwCBQoSGlobalAclSlotID }
            ::= { hwCBQoSGlobalAclNotSupportAlarmTable 1 }
            
              HwCBQoSGlobalAclNotSupportAlarmEntry ::=
            SEQUENCE { 
                  hwCBQoSGlobalAclDirection
                    OCTET STRING,
                  hwCBQoSGlobalAclSlotID      
                        Integer32
                 }
                 
            hwCBQoSGlobalAclDirection OBJECT-TYPE
                    SYNTAX OCTET STRING (SIZE (1..31))
                MAX-ACCESS read-only
                STATUS current
                DESCRIPTION
                "hwCBQoSGlobalAclDirection"
                 ::= { hwCBQoSGlobalAclNotSupportAlarmEntry 1 }
                 
            hwCBQoSGlobalAclSlotID OBJECT-TYPE
                    SYNTAX Integer32 (1..128)
                MAX-ACCESS read-only
                STATUS current
                DESCRIPTION
                "hwCBQoSGlobalAclSlotID"
                 ::= { hwCBQoSGlobalAclNotSupportAlarmEntry 2 }     
		--end by zhangyong 00291234
        --Beg: mod by l00200458 on 20160528                        
       hwCBQoSUpdateUserQueueResourceNotEnoughAlarmTable OBJECT-TYPE
                        SYNTAX SEQUENCE OF HwCBQoSUpdateUserQueueResourceNotEnoughAlarmEntry
                        MAX-ACCESS not-accessible
                        STATUS current
                        DESCRIPTION
                                "hwCBQoSUpdateUserQueueResourceNotEnoughAlarmTable"
                        ::= { hwCBQoSApplyPolicyObjects 13 }
                        
              hwCBQoSUpdateUserQueueResourceNotEnoughAlarmEntry OBJECT-TYPE
            SYNTAX HwCBQoSUpdateUserQueueResourceNotEnoughAlarmEntry
            MAX-ACCESS not-accessible
            STATUS current
            DESCRIPTION
                "hwCBQoSUpdateUserQueueResourceNotEnoughAlarmEntry"
            INDEX { hwCBQoSUpdateUserQueueBehaviorName, hwCBQoSUpdateUserQueueSlotID, hwCBQoSUpdateUserQueueCir, hwCBQoSUpdateUserQueuePir }
            ::= { hwCBQoSUpdateUserQueueResourceNotEnoughAlarmTable 1 }
            
              HwCBQoSUpdateUserQueueResourceNotEnoughAlarmEntry ::=
            SEQUENCE { 
                  hwCBQoSUpdateUserQueueBehaviorName
                    OCTET STRING,
                  hwCBQoSUpdateUserQueueSlotID      
                        Integer32,
                  hwCBQoSUpdateUserQueueCir
                        Integer32,
                  hwCBQoSUpdateUserQueuePir
                        Integer32
                 }
                 
            hwCBQoSUpdateUserQueueBehaviorName OBJECT-TYPE
                    SYNTAX OCTET STRING (SIZE (1..31))
                MAX-ACCESS read-only
                STATUS current
                DESCRIPTION
                "hwCBQoSUpdateUserQueueBehaviorName"
                 ::= { hwCBQoSUpdateUserQueueResourceNotEnoughAlarmEntry 1 }
                 
            hwCBQoSUpdateUserQueueSlotID OBJECT-TYPE
                    SYNTAX Integer32 (1..128)
                MAX-ACCESS read-only
                STATUS current
                DESCRIPTION
                "hwCBQoSUpdateUserQueueSlotID"
                 ::= { hwCBQoSUpdateUserQueueResourceNotEnoughAlarmEntry 2 }     
            hwCBQoSUpdateUserQueueCir OBJECT-TYPE
                    SYNTAX Integer32 (0..4294967295)
                MAX-ACCESS read-only
                STATUS current
                DESCRIPTION
                "hwCBQoSUpdateUserQueueCir"
                 ::= { hwCBQoSUpdateUserQueueResourceNotEnoughAlarmEntry 3 }                  
            hwCBQoSUpdateUserQueuePir OBJECT-TYPE
                    SYNTAX Integer32 (0..4294967295)
                MAX-ACCESS read-only
                STATUS current
                DESCRIPTION
                "hwCBQoSUpdateUserQueuePir"
                 ::= { hwCBQoSUpdateUserQueueResourceNotEnoughAlarmEntry 4 }                  

       hwCBQoSSetUserQueueResourceNotEnoughAlarmTable OBJECT-TYPE
                        SYNTAX SEQUENCE OF HwCBQoSSetUserQueueResourceNotEnoughAlarmEntry
                        MAX-ACCESS not-accessible
                        STATUS current
                        DESCRIPTION
                                "hwCBQoSSetUserQueueResourceNotEnoughAlarmTable"
                        ::= { hwCBQoSApplyPolicyObjects 14 }
                        
              hwCBQoSSetUserQueueResourceNotEnoughAlarmEntry OBJECT-TYPE
            SYNTAX HwCBQoSSetUserQueueResourceNotEnoughAlarmEntry
            MAX-ACCESS not-accessible
            STATUS current
            DESCRIPTION
                "hwCBQoSSetUserQueueResourceNotEnoughAlarmEntry"
            INDEX { hwCBQoSSetUserQueueBehaviorName, hwCBQoSSetUserQueueSlotID }
            ::= { hwCBQoSSetUserQueueResourceNotEnoughAlarmTable 1 }
            
              HwCBQoSSetUserQueueResourceNotEnoughAlarmEntry ::=
            SEQUENCE { 
                  hwCBQoSSetUserQueueBehaviorName
                    OCTET STRING,
                  hwCBQoSSetUserQueueSlotID      
                        Integer32
                 }
                 
            hwCBQoSSetUserQueueBehaviorName OBJECT-TYPE
                    SYNTAX OCTET STRING (SIZE (1..31))
                MAX-ACCESS read-only
                STATUS current
                DESCRIPTION
                "hwCBQoSSetUserQueueBehaviorName"
                 ::= { hwCBQoSSetUserQueueResourceNotEnoughAlarmEntry 1 }
                 
            hwCBQoSSetUserQueueSlotID OBJECT-TYPE
                    SYNTAX Integer32 (1..128)
                MAX-ACCESS read-only
                STATUS current
                DESCRIPTION
                "hwCBQoSSetUserQueueSlotID"
                 ::= { hwCBQoSSetUserQueueResourceNotEnoughAlarmEntry 2 }                
        --End: mod by l00200458 on 20160528                        

-- multi-policy applied on global
                hwCBQoSGlobalApplyMultiPolicyTable OBJECT-TYPE
                        SYNTAX SEQUENCE OF HwCBQoSGlobalApplyMultiPolicyEntry
                        MAX-ACCESS not-accessible
                        STATUS current
                        DESCRIPTION
                                "A table of applying multi-policy on global."
                        ::= { hwCBQoSApplyPolicyObjects 15 }

                
                hwCBQoSGlobalApplyMultiPolicyEntry OBJECT-TYPE
                        SYNTAX HwCBQoSGlobalApplyMultiPolicyEntry
                        MAX-ACCESS not-accessible
                        STATUS current
                        DESCRIPTION
                                "Policy applied on global Configuration Information Entry."
                        INDEX { hwCBQoSGlobalApplyMultiPolicyChassisId, hwCBQoSGlobalApplyMultiPolicySlotId, hwCBQoSGlobalApplyMultiPolicyDirection, hwCBQoSGlobalApplyMultiPolicyIndex}
                        ::= { hwCBQoSGlobalApplyMultiPolicyTable 1 }

                
                HwCBQoSGlobalApplyMultiPolicyEntry::=
                        SEQUENCE 
                        { 
                            hwCBQoSGlobalApplyMultiPolicyChassisId
                                    Integer32,
                            hwCBQoSGlobalApplyMultiPolicySlotId
                                    Integer32,
                            hwCBQoSGlobalApplyMultiPolicyDirection
                                    INTEGER,
                            hwCBQoSGlobalApplyMultiPolicyIndex
                                    Integer32,
                            hwCBQoSGlobalApplyMultiPolicyName
                                    OCTET STRING,
                            hwCBQoSGlobalApplyMultiPolicyRowStatus
                                    RowStatus
                         }

                hwCBQoSGlobalApplyMultiPolicyChassisId OBJECT-TYPE
                        SYNTAX Integer32
                        MAX-ACCESS read-only
                        STATUS current
                        DESCRIPTION
                                "Chassis ID. When both this node and the next node(hwCBQoSGlobalApplyMultiPolicySlotId) are 0, it identifies all slot."
                        ::= { hwCBQoSGlobalApplyMultiPolicyEntry 1 }

                hwCBQoSGlobalApplyMultiPolicySlotId OBJECT-TYPE
                        SYNTAX Integer32
                        MAX-ACCESS read-only
                        STATUS current
                        DESCRIPTION
                                "slot ID. When both this node and the previous node(hwCBQoSGlobalApplyMultiPolicyChassisId) are 0, it identifies all slot."
                        ::= { hwCBQoSGlobalApplyMultiPolicyEntry 2 }

                
                hwCBQoSGlobalApplyMultiPolicyDirection OBJECT-TYPE
                        SYNTAX INTEGER
                        {
                            inbound(1),
                            outbound(2)
                        }
                        MAX-ACCESS read-only
                        STATUS current
                        DESCRIPTION
                                "Policy Direction:
                                 inbound(1), apply policy inbound;
                                 outbound(2), apply policy outbound."
                        ::= { hwCBQoSGlobalApplyMultiPolicyEntry 3 }

                hwCBQoSGlobalApplyMultiPolicyIndex OBJECT-TYPE
	       SYNTAX Integer32
	       MAX-ACCESS read-only
	       STATUS current
	       DESCRIPTION
		"The value of this object identifies the policy index."
                        ::= { hwCBQoSGlobalApplyMultiPolicyEntry 4 }
                
                hwCBQoSGlobalApplyMultiPolicyName OBJECT-TYPE
                        SYNTAX OCTET STRING (SIZE (1..31))
                        MAX-ACCESS read-only
                        STATUS current
                        DESCRIPTION
                                "Name of the applied policy."
                        ::= { hwCBQoSGlobalApplyMultiPolicyEntry 5 }

                
                hwCBQoSGlobalApplyMultiPolicyRowStatus OBJECT-TYPE
                        SYNTAX RowStatus
                        MAX-ACCESS read-create
                        STATUS current
                        DESCRIPTION
                                "RowStatus. Three actions are used: active, createAndGo, destroy."
                        ::= { hwCBQoSGlobalApplyMultiPolicyEntry 6 }
                
--  Running statistics information
        hwCBQoSApplyPolicyStaticsObjects OBJECT IDENTIFIER ::= { hwCBQoSObjects 5 }

        
--  Interface: policy Running statistics information
        hwCBQoSIfStaticsObjects OBJECT IDENTIFIER ::= { hwCBQoSApplyPolicyStaticsObjects 1 }

        
--  Interface CBQ statistics
        hwCBQoSIfCbqRunInfoTable OBJECT-TYPE
            SYNTAX SEQUENCE OF HwCBQoSIfCbqRunInfoEntry
            MAX-ACCESS not-accessible
            STATUS current
            DESCRIPTION
                "A table of interface CBQ Running statistics. When policy using queue behavior is applied on
                interface the interface will using Class Based Queuing."
            ::= { hwCBQoSIfStaticsObjects 1 }

        
        hwCBQoSIfCbqRunInfoEntry OBJECT-TYPE
            SYNTAX HwCBQoSIfCbqRunInfoEntry
            MAX-ACCESS not-accessible
            STATUS current
            DESCRIPTION
                "Interface CBQ statistics entry."
            INDEX { hwCBQoSIfApplyPolicyIfIndex }
            ::= { hwCBQoSIfCbqRunInfoTable 1 }

        
        HwCBQoSIfCbqRunInfoEntry ::=
            SEQUENCE { 
                hwCBQoSIfCbqQueueSize
                    Integer32,
                hwCBQoSIfCbqDiscard
                    Counter64,
                hwCBQoSIfCbqEfQueueSize
                    Integer32,
                hwCBQoSIfCbqAfQueueSize
                    Integer32,
                hwCBQoSIfCbqBeQueueSize
                    Integer32,
                hwCBQoSIfCbqBeActiveQueueNum
                    Integer32,
                hwCBQoSIfCbqBeMaxActiveQueueNum
                    Integer32,
                hwCBQoSIfCbqBeTotalQueueNum
                    Integer32,
                hwCBQoSIfCbqAfAllocatedQueueNum
                    Integer32
             }

        hwCBQoSIfCbqQueueSize OBJECT-TYPE
            SYNTAX Integer32
            MAX-ACCESS read-only
            STATUS current
            DESCRIPTION
                "Queue size of CBQ"
            ::= { hwCBQoSIfCbqRunInfoEntry 1 }

        
        hwCBQoSIfCbqDiscard OBJECT-TYPE
            SYNTAX Counter64
            MAX-ACCESS read-only
            STATUS current
            DESCRIPTION
                "The number of discarded packets which coundn't be enqueued."
            ::= { hwCBQoSIfCbqRunInfoEntry 2 }

        
        hwCBQoSIfCbqEfQueueSize OBJECT-TYPE
            SYNTAX Integer32
            MAX-ACCESS read-only
            STATUS current
            DESCRIPTION
                "Queue size of EF"
            ::= { hwCBQoSIfCbqRunInfoEntry 3 }

        
        hwCBQoSIfCbqAfQueueSize OBJECT-TYPE
            SYNTAX Integer32
            MAX-ACCESS read-only
            STATUS current
            DESCRIPTION
                "Queue size of AF"
            ::= { hwCBQoSIfCbqRunInfoEntry 4 }

        
        hwCBQoSIfCbqBeQueueSize OBJECT-TYPE
            SYNTAX Integer32
            MAX-ACCESS read-only
            STATUS current
            DESCRIPTION
                "Queue size of BE"
            ::= { hwCBQoSIfCbqRunInfoEntry 5 }

        
        hwCBQoSIfCbqBeActiveQueueNum OBJECT-TYPE
            SYNTAX Integer32
            MAX-ACCESS read-only
            STATUS current
            DESCRIPTION
                "the number of Active Be Queue"
            ::= { hwCBQoSIfCbqRunInfoEntry 6 }

        
        hwCBQoSIfCbqBeMaxActiveQueueNum OBJECT-TYPE
            SYNTAX Integer32
            MAX-ACCESS read-only
            STATUS current
            DESCRIPTION
                "the max number of Active Be Queue"
            ::= { hwCBQoSIfCbqRunInfoEntry 7 }

        
        hwCBQoSIfCbqBeTotalQueueNum OBJECT-TYPE
            SYNTAX Integer32
            MAX-ACCESS read-only
            STATUS current
            DESCRIPTION
                "the total number of Be Queue"
            ::= { hwCBQoSIfCbqRunInfoEntry 8 }

        
        hwCBQoSIfCbqAfAllocatedQueueNum OBJECT-TYPE
            SYNTAX Integer32
            MAX-ACCESS read-only
            STATUS current
            DESCRIPTION
                "the Allocated number of Af Queue"
            ::= { hwCBQoSIfCbqRunInfoEntry 9 }

        
--  Class match statistics
        hwCBQoSIfClassMatchRunInfoTable OBJECT-TYPE
            SYNTAX SEQUENCE OF HwCBQoSIfClassMatchRunInfoEntry
            MAX-ACCESS not-accessible
            STATUS current
            DESCRIPTION
                "A table of Running statistics for matching a classifier
                in a QoS policy applied on the interface."
            ::= { hwCBQoSIfStaticsObjects 2 }

        
        hwCBQoSIfClassMatchRunInfoEntry OBJECT-TYPE
            SYNTAX HwCBQoSIfClassMatchRunInfoEntry
            MAX-ACCESS not-accessible
            STATUS current
            DESCRIPTION
                "Classifier's matching statistics information entry."
            INDEX { hwCBQoSIfApplyPolicyIfIndex, hwCBQoSIfApplyPolicyDirection, hwCBQoSPolicyClassIndex }
            ::= { hwCBQoSIfClassMatchRunInfoTable 1 }

        
        HwCBQoSIfClassMatchRunInfoEntry ::=
            SEQUENCE { 
                hwCBQoSIfClassMatchedPackets
                    Counter64,
                hwCBQoSIfClassMatchedBytes
                    Counter64,
                hwCBQoSIfClassAverageRate
                    Counter64,
                hwCBQosIfClassPassedPackets
                    Counter64,
                hwCBQosIfClassDroppedPackets
                    Counter64
             }

        hwCBQoSIfClassMatchedPackets OBJECT-TYPE
            SYNTAX Counter64
            MAX-ACCESS read-only
            STATUS current
            DESCRIPTION
                "Number of packets matching a class in a QoS policy."
            ::= { hwCBQoSIfClassMatchRunInfoEntry 1 }

        
        hwCBQoSIfClassMatchedBytes OBJECT-TYPE
            SYNTAX Counter64
            MAX-ACCESS read-only
            STATUS current
            DESCRIPTION
                "Number of bytes matching a class in a QoS policy.
                Only software QoS support this node."
            ::= { hwCBQoSIfClassMatchRunInfoEntry 2 }

        
        hwCBQoSIfClassAverageRate OBJECT-TYPE
            SYNTAX Counter64
            MAX-ACCESS read-only
            STATUS current
            DESCRIPTION
                "Average rate of the traffic matching a class in a QoS policy.
                For inbound QoS policy, it is the rate of the traffic input;
                For outbound QoS policy, it is the rate of the traffic output.
                Only software QoS support this node."
            ::= { hwCBQoSIfClassMatchRunInfoEntry 3 }

        hwCBQosIfClassPassedPackets OBJECT-TYPE
            SYNTAX Counter64
            MAX-ACCESS read-only
            STATUS current
            DESCRIPTION
                "Number of passed packets matching a class in a QoS policy."
            ::= { hwCBQoSIfClassMatchRunInfoEntry 4 }

        hwCBQosIfClassDroppedPackets OBJECT-TYPE
            SYNTAX Counter64
            MAX-ACCESS read-only
            STATUS current
            DESCRIPTION
                "Number of dropped packets matching a class in a QoS policy."
            ::= { hwCBQoSIfClassMatchRunInfoEntry 5 }      
        
--  CAR statistics
        hwCBQoSIfCarRunInfoTable OBJECT-TYPE
            SYNTAX SEQUENCE OF HwCBQoSIfCarRunInfoEntry
            MAX-ACCESS not-accessible
            STATUS current
            DESCRIPTION
                "A table of Running statistics for CAR
                in a QoS policy applied on the interface."
            ::= { hwCBQoSIfStaticsObjects 3 }

    hwCBQoSIfCarRunInfoEntry OBJECT-TYPE
        SYNTAX HwCBQoSIfCarRunInfoEntry
        MAX-ACCESS not-accessible
        STATUS current
        DESCRIPTION
            "CAR statistics information entry."
        INDEX { hwCBQoSIfApplyPolicyIfIndex, hwCBQoSIfApplyPolicyDirection, hwCBQoSIfVlanApplyPolicyVlanid1, 
            hwCBQoSPolicyClassIndex }
        ::= { hwCBQoSIfCarRunInfoTable 1 }

        
        HwCBQoSIfCarRunInfoEntry ::=
            SEQUENCE { 
                hwCBQoSIfCarGreenPassedPackets
                    Counter64,
                hwCBQoSIfCarGreenPassedBytes
                    Counter64,
                hwCBQoSIfCarGreenRemarkedPackets
                    Counter64,
                hwCBQoSIfCarGreenRemarkedBytes
                    Counter64,
                hwCBQoSIfCarGreenDiscardedPackets
                    Counter64,
                hwCBQoSIfCarGreenDiscardedBytes
                    Counter64,
                hwCBQoSIfCarYellowPassedPackets
                    Counter64,
                hwCBQoSIfCarYellowPassedBytes
                    Counter64,
                hwCBQoSIfCarYellowRemarkedPackets
                    Counter64,
                hwCBQoSIfCarYellowRemarkedBytes
                    Counter64,
                hwCBQoSIfCarYellowDiscardedPackets
                    Counter64,
                hwCBQoSIfCarYellowDiscardedBytes
                    Counter64,
                hwCBQoSIfCarRedPassedPackets
                    Counter64,
                hwCBQoSIfCarRedPassedBytes
                    Counter64,
                hwCBQoSIfCarRedRemarkedPackets
                    Counter64,
                hwCBQoSIfCarRedRemarkedBytes
                    Counter64,
                hwCBQoSIfCarRedDiscardedPackets
                    Counter64,
                hwCBQoSIfCarRedDiscardedBytes
                    Counter64,
                hwCBQoSIfCarGreenPassedPacketsRate
                    Counter64,
                hwCBQoSIfCarGreenPassedBytesRate
                    Counter64,
                hwCBQoSIfCarGreenRemarkedPacketsRate
                    Counter64,
                hwCBQoSIfCarGreenRemarkedBytesRate
                    Counter64,
                hwCBQoSIfCarGreenDiscardedPacketsRate
                    Counter64,
                hwCBQoSIfCarGreenDiscardedBytesRate
                    Counter64,
                hwCBQoSIfCarYellowPassedPacketsRate
                    Counter64,
                hwCBQoSIfCarYellowPassedBytesRate
                    Counter64,
                hwCBQoSIfCarYellowRemarkedPacketsRate
                    Counter64,
                hwCBQoSIfCarYellowRemarkedBytesRate
                    Counter64,
                hwCBQoSIfCarYellowDiscardedPacketsRate
                    Counter64,
                hwCBQoSIfCarYellowDiscardedBytesRate
                    Counter64,
                hwCBQoSIfCarRedPassedPacketsRate
                    Counter64,
                hwCBQoSIfCarRedPassedBytesRate
                    Counter64,
                hwCBQoSIfCarRedRemarkedPacketsRate
                    Counter64,
                hwCBQoSIfCarRedRemarkedBytesRate
                    Counter64,
                hwCBQoSIfCarRedDiscardedPacketsRate
                    Counter64,
                hwCBQoSIfCarRedDiscardedBytesRate
                    Counter64
             }

        hwCBQoSIfCarGreenPassedPackets OBJECT-TYPE
            SYNTAX Counter64
            MAX-ACCESS read-only
            STATUS current
            DESCRIPTION
                "Passed packets of green packet"
            ::= { hwCBQoSIfCarRunInfoEntry 1 }

        
        hwCBQoSIfCarGreenPassedBytes OBJECT-TYPE
            SYNTAX Counter64
            MAX-ACCESS read-only
            STATUS current
            DESCRIPTION
                "Passed bytes of green packet"
            ::= { hwCBQoSIfCarRunInfoEntry 2 }

        
        hwCBQoSIfCarGreenRemarkedPackets OBJECT-TYPE
            SYNTAX Counter64
            MAX-ACCESS read-only
            STATUS current
            DESCRIPTION
                "Remarked packets of green packet"
            ::= { hwCBQoSIfCarRunInfoEntry 3 }

        
        hwCBQoSIfCarGreenRemarkedBytes OBJECT-TYPE
            SYNTAX Counter64
            MAX-ACCESS read-only
            STATUS current
            DESCRIPTION
                "Remarked bytes of green packet"
            ::= { hwCBQoSIfCarRunInfoEntry 4 }

        
        hwCBQoSIfCarGreenDiscardedPackets OBJECT-TYPE
            SYNTAX Counter64
            MAX-ACCESS read-only
            STATUS current
            DESCRIPTION
                "Discarded packets of green packet"
            ::= { hwCBQoSIfCarRunInfoEntry 5 }

        
        hwCBQoSIfCarGreenDiscardedBytes OBJECT-TYPE
            SYNTAX Counter64
            MAX-ACCESS read-only
            STATUS current
            DESCRIPTION
                "Discarded bytes of green packet"
            ::= { hwCBQoSIfCarRunInfoEntry 6 }

        
        hwCBQoSIfCarYellowPassedPackets OBJECT-TYPE
            SYNTAX Counter64
            MAX-ACCESS read-only
            STATUS current
            DESCRIPTION
                "Passed packets of yellow packet"
            ::= { hwCBQoSIfCarRunInfoEntry 7 }

        
        hwCBQoSIfCarYellowPassedBytes OBJECT-TYPE
            SYNTAX Counter64
            MAX-ACCESS read-only
            STATUS current
            DESCRIPTION
                "Passed bytes of yellow packet"
            ::= { hwCBQoSIfCarRunInfoEntry 8 }

        
        hwCBQoSIfCarYellowRemarkedPackets OBJECT-TYPE
            SYNTAX Counter64
            MAX-ACCESS read-only
            STATUS current
            DESCRIPTION
                "Remarked packets of yellow packet"
            ::= { hwCBQoSIfCarRunInfoEntry 9 }

        
        hwCBQoSIfCarYellowRemarkedBytes OBJECT-TYPE
            SYNTAX Counter64
            MAX-ACCESS read-only
            STATUS current
            DESCRIPTION
                "Remarked bytes of yellow packet"
            ::= { hwCBQoSIfCarRunInfoEntry 10 }

        
        hwCBQoSIfCarYellowDiscardedPackets OBJECT-TYPE
            SYNTAX Counter64
            MAX-ACCESS read-only
            STATUS current
            DESCRIPTION
                "Discarded packets of yellow packet"
            ::= { hwCBQoSIfCarRunInfoEntry 11 }

        
        hwCBQoSIfCarYellowDiscardedBytes OBJECT-TYPE
            SYNTAX Counter64
            MAX-ACCESS read-only
            STATUS current
            DESCRIPTION
                "Discarded bytes of yellow packet"
            ::= { hwCBQoSIfCarRunInfoEntry 12 }

        
        hwCBQoSIfCarRedPassedPackets OBJECT-TYPE
            SYNTAX Counter64
            MAX-ACCESS read-only
            STATUS current
            DESCRIPTION
                "Passed packets of red packet"
            ::= { hwCBQoSIfCarRunInfoEntry 13 }

        
        hwCBQoSIfCarRedPassedBytes OBJECT-TYPE
            SYNTAX Counter64
            MAX-ACCESS read-only
            STATUS current
            DESCRIPTION
                "Passed bytes of red packet"
            ::= { hwCBQoSIfCarRunInfoEntry 14 }

        
        hwCBQoSIfCarRedRemarkedPackets OBJECT-TYPE
            SYNTAX Counter64
            MAX-ACCESS read-only
            STATUS current
            DESCRIPTION
                "Remarked packets of red packet"
            ::= { hwCBQoSIfCarRunInfoEntry 15 }

        
        hwCBQoSIfCarRedRemarkedBytes OBJECT-TYPE
            SYNTAX Counter64
            MAX-ACCESS read-only
            STATUS current
            DESCRIPTION
                "Remarked bytes of red packet"
            ::= { hwCBQoSIfCarRunInfoEntry 16 }

        
        hwCBQoSIfCarRedDiscardedPackets OBJECT-TYPE
            SYNTAX Counter64
            MAX-ACCESS read-only
            STATUS current
            DESCRIPTION
                "Discarded packets of red packet"
            ::= { hwCBQoSIfCarRunInfoEntry 17 }

        
        hwCBQoSIfCarRedDiscardedBytes OBJECT-TYPE
            SYNTAX Counter64
            MAX-ACCESS read-only
            STATUS current
            DESCRIPTION
                "Discarded bytes of red packet"
            ::= { hwCBQoSIfCarRunInfoEntry 18 }

        hwCBQoSIfCarGreenPassedPacketsRate OBJECT-TYPE
            SYNTAX Counter64
            MAX-ACCESS read-only
            STATUS current
            DESCRIPTION
                "Rate of forwarded green packets"
            ::= { hwCBQoSIfCarRunInfoEntry 19 }

        
        hwCBQoSIfCarGreenPassedBytesRate OBJECT-TYPE
            SYNTAX Counter64
            MAX-ACCESS read-only
            STATUS current
            DESCRIPTION
                "Rate of forwarded bytes of green packets"
            ::= { hwCBQoSIfCarRunInfoEntry 20 }

        
        hwCBQoSIfCarGreenRemarkedPacketsRate OBJECT-TYPE
            SYNTAX Counter64
            MAX-ACCESS read-only
            STATUS current
            DESCRIPTION
                "Rate of re-marked green packets"
            ::= { hwCBQoSIfCarRunInfoEntry 21 }

        
        hwCBQoSIfCarGreenRemarkedBytesRate OBJECT-TYPE
            SYNTAX Counter64
            MAX-ACCESS read-only
            STATUS current
            DESCRIPTION
                "Rate of re-marked bytes of green packets"
            ::= { hwCBQoSIfCarRunInfoEntry 22 }

        
        hwCBQoSIfCarGreenDiscardedPacketsRate OBJECT-TYPE
            SYNTAX Counter64
            MAX-ACCESS read-only
            STATUS current
            DESCRIPTION
                "Rate of discarded green packets"
            ::= { hwCBQoSIfCarRunInfoEntry 23 }

        
        hwCBQoSIfCarGreenDiscardedBytesRate OBJECT-TYPE
            SYNTAX Counter64
            MAX-ACCESS read-only
            STATUS current
            DESCRIPTION
                "Rate of discarded bytes of green packets"
            ::= { hwCBQoSIfCarRunInfoEntry 24 }

        
        hwCBQoSIfCarYellowPassedPacketsRate OBJECT-TYPE
            SYNTAX Counter64
            MAX-ACCESS read-only
            STATUS current
            DESCRIPTION
                "Rate of forwarded yellow packets"
            ::= { hwCBQoSIfCarRunInfoEntry 25 }

        
        hwCBQoSIfCarYellowPassedBytesRate OBJECT-TYPE
            SYNTAX Counter64
            MAX-ACCESS read-only
            STATUS current
            DESCRIPTION
                "Rate of forwarded bytes of yellow packets"
            ::= { hwCBQoSIfCarRunInfoEntry 26 }

        
        hwCBQoSIfCarYellowRemarkedPacketsRate OBJECT-TYPE
            SYNTAX Counter64
            MAX-ACCESS read-only
            STATUS current
            DESCRIPTION
                "Rate of re-marked yellow packets"
            ::= { hwCBQoSIfCarRunInfoEntry 27 }

        
        hwCBQoSIfCarYellowRemarkedBytesRate OBJECT-TYPE
            SYNTAX Counter64
            MAX-ACCESS read-only
            STATUS current
            DESCRIPTION
                "Rate of re-marked bytes of yellow packets"
            ::= { hwCBQoSIfCarRunInfoEntry 28 }

        
        hwCBQoSIfCarYellowDiscardedPacketsRate OBJECT-TYPE
            SYNTAX Counter64
            MAX-ACCESS read-only
            STATUS current
            DESCRIPTION
                "Rate of discarded yellow packets"
            ::= { hwCBQoSIfCarRunInfoEntry 29 }

        
        hwCBQoSIfCarYellowDiscardedBytesRate OBJECT-TYPE
            SYNTAX Counter64
            MAX-ACCESS read-only
            STATUS current
            DESCRIPTION
                "Rate of discarded bytes of yellow packets"
            ::= { hwCBQoSIfCarRunInfoEntry 30 }

        
        hwCBQoSIfCarRedPassedPacketsRate OBJECT-TYPE
            SYNTAX Counter64
            MAX-ACCESS read-only
            STATUS current
            DESCRIPTION
                "Rate of forwarded red packets"
            ::= { hwCBQoSIfCarRunInfoEntry 31 }

        
        hwCBQoSIfCarRedPassedBytesRate OBJECT-TYPE
            SYNTAX Counter64
            MAX-ACCESS read-only
            STATUS current
            DESCRIPTION
                "Rate of forwarded bytes of red packets"
            ::= { hwCBQoSIfCarRunInfoEntry 32 }

        
        hwCBQoSIfCarRedRemarkedPacketsRate OBJECT-TYPE
            SYNTAX Counter64
            MAX-ACCESS read-only
            STATUS current
            DESCRIPTION
                "Rate of re-marked red packets"
            ::= { hwCBQoSIfCarRunInfoEntry 33 }

        
        hwCBQoSIfCarRedRemarkedBytesRate OBJECT-TYPE
            SYNTAX Counter64
            MAX-ACCESS read-only
            STATUS current
            DESCRIPTION
                "Rate of re-marked bytes of red packets"
            ::= { hwCBQoSIfCarRunInfoEntry 34 }

        
        hwCBQoSIfCarRedDiscardedPacketsRate OBJECT-TYPE
            SYNTAX Counter64
            MAX-ACCESS read-only
            STATUS current
            DESCRIPTION
                "Rate of discarded red packets"
            ::= { hwCBQoSIfCarRunInfoEntry 35 }

        
        hwCBQoSIfCarRedDiscardedBytesRate OBJECT-TYPE
            SYNTAX Counter64
            MAX-ACCESS read-only
            STATUS current
            DESCRIPTION
                "Rate of discarded bytes of red packets"
            ::= { hwCBQoSIfCarRunInfoEntry 36 }
        
--  GTS statistics
        hwCBQoSIfGtsRunInfoTable OBJECT-TYPE
            SYNTAX SEQUENCE OF HwCBQoSIfGtsRunInfoEntry
            MAX-ACCESS not-accessible
            STATUS current
            DESCRIPTION
                "A table of Running statistics for GTS
                in a QoS policy applied on the interface."
            ::= { hwCBQoSIfStaticsObjects 4 }

        
        hwCBQoSIfGtsRunInfoEntry OBJECT-TYPE
            SYNTAX HwCBQoSIfGtsRunInfoEntry
            MAX-ACCESS not-accessible
            STATUS current
            DESCRIPTION
                "GTS statistics entry."
            INDEX { hwCBQoSIfApplyPolicyIfIndex, hwCBQoSIfApplyPolicyDirection, hwCBQoSPolicyClassIndex }
            ::= { hwCBQoSIfGtsRunInfoTable 1 }

        
        HwCBQoSIfGtsRunInfoEntry ::=
            SEQUENCE { 
                hwCBQoSIfGtsPassedPackets
                    Counter64,
                hwCBQoSIfGtsPassedBytes
                    Counter64,
                hwCBQoSIfGtsDiscardedPackets
                    Counter64,
                hwCBQoSIfGtsDiscardedBytes
                    Counter64,
                hwCBQoSIfGtsDelayedPackets
                    Counter64,
                hwCBQoSIfGtsDelayedBytes
                    Counter64,
                hwCBQoSIfGtsQueueSize
                    Integer32
             }

        hwCBQoSIfGtsPassedPackets OBJECT-TYPE
            SYNTAX Counter64
            MAX-ACCESS read-only
            STATUS current
            DESCRIPTION
                "Number of packets passed by GTS."
            ::= { hwCBQoSIfGtsRunInfoEntry 1 }

        
        hwCBQoSIfGtsPassedBytes OBJECT-TYPE
            SYNTAX Counter64
            MAX-ACCESS read-only
            STATUS current
            DESCRIPTION
                "Number of bytes passed by GTS."
            ::= { hwCBQoSIfGtsRunInfoEntry 2 }

        
        hwCBQoSIfGtsDiscardedPackets OBJECT-TYPE
            SYNTAX Counter64
            MAX-ACCESS read-only
            STATUS current
            DESCRIPTION
                "Number of packets discarded by GTS."
            ::= { hwCBQoSIfGtsRunInfoEntry 3 }

        
        hwCBQoSIfGtsDiscardedBytes OBJECT-TYPE
            SYNTAX Counter64
            MAX-ACCESS read-only
            STATUS current
            DESCRIPTION
                "Number of bytes discarded by GTS."
            ::= { hwCBQoSIfGtsRunInfoEntry 4 }

        
        hwCBQoSIfGtsDelayedPackets OBJECT-TYPE
            SYNTAX Counter64
            MAX-ACCESS read-only
            STATUS current
            DESCRIPTION
                "Number of packets delayed by GTS."
            ::= { hwCBQoSIfGtsRunInfoEntry 5 }

        
        hwCBQoSIfGtsDelayedBytes OBJECT-TYPE
            SYNTAX Counter64
            MAX-ACCESS read-only
            STATUS current
            DESCRIPTION
                "Number of bytes delayed by GTS."
            ::= { hwCBQoSIfGtsRunInfoEntry 6 }

        
        hwCBQoSIfGtsQueueSize OBJECT-TYPE
            SYNTAX Integer32
            MAX-ACCESS read-only
            STATUS current
            DESCRIPTION
                "Queue size of GTS queue."
            ::= { hwCBQoSIfGtsRunInfoEntry 7 }

        
--  Remark statistics
        hwCBQoSIfRemarkRunInfoTable OBJECT-TYPE
            SYNTAX SEQUENCE OF HwCBQoSIfRemarkRunInfoEntry
            MAX-ACCESS not-accessible
            STATUS current
            DESCRIPTION
                "A table of Running statistics for remarking
                in a QoS policy applied on the interface."
            ::= { hwCBQoSIfStaticsObjects 5 }

        
        hwCBQoSIfRemarkRunInfoEntry OBJECT-TYPE
            SYNTAX HwCBQoSIfRemarkRunInfoEntry
            MAX-ACCESS not-accessible
            STATUS current
            DESCRIPTION
                "Remarking statistics entry."
            INDEX { hwCBQoSIfApplyPolicyIfIndex, hwCBQoSIfApplyPolicyDirection, hwCBQoSPolicyClassIndex }
            ::= { hwCBQoSIfRemarkRunInfoTable 1 }

        
        HwCBQoSIfRemarkRunInfoEntry ::=
            SEQUENCE { 
                hwCBQoSIfRemarkedPackets
                    Counter64,
                hwCBQoSIfRemarkedBytes
                    Counter64
             }

        hwCBQoSIfRemarkedPackets OBJECT-TYPE
            SYNTAX Counter64
            MAX-ACCESS read-only
            STATUS current
            DESCRIPTION
                "Number of packets remarked."
            ::= { hwCBQoSIfRemarkRunInfoEntry 1 }

        
        hwCBQoSIfRemarkedBytes OBJECT-TYPE
            SYNTAX Counter64
            MAX-ACCESS read-only
            STATUS current
            DESCRIPTION
                "Number of bytes remarked."
            ::= { hwCBQoSIfRemarkRunInfoEntry 2 }

        
--  Queue statistics
        hwCBQoSIfQueueRunInfoTable OBJECT-TYPE
            SYNTAX SEQUENCE OF HwCBQoSIfQueueRunInfoEntry
            MAX-ACCESS not-accessible
            STATUS current
            DESCRIPTION
                "A table of Running statistics for queue
                in a QoS policy applied on the interface."
            ::= { hwCBQoSIfStaticsObjects 6 }

        
        hwCBQoSIfQueueRunInfoEntry OBJECT-TYPE
            SYNTAX HwCBQoSIfQueueRunInfoEntry
            MAX-ACCESS not-accessible
            STATUS current
            DESCRIPTION
                "Queue statistics entry."
            INDEX { hwCBQoSIfApplyPolicyIfIndex, hwCBQoSIfApplyPolicyDirection, hwCBQoSPolicyClassIndex }
            ::= { hwCBQoSIfQueueRunInfoTable 1 }

        
        HwCBQoSIfQueueRunInfoEntry ::=
            SEQUENCE { 
                hwCBQoSIfQueueMatchedPackets
                    Counter64,
                hwCBQoSIfQueueMatchedBytes
                    Counter64,
                hwCBQoSIfQueueEnqueuedPackets
                    Counter64,
                hwCBQoSIfQueueEnqueuedBytes
                    Counter64,
                hwCBQoSIfQueueDiscardedPackets
                    Counter64,
                hwCBQoSIfQueueDiscardedBytes
                    Counter64,
                hwCBQoSIfQueueMatchedPacketsRate
                    Counter64,
                hwCBQoSIfQueueMatchedBytesRate
                    Counter64,
                hwCBQoSIfQueueEnqueuedPacketsRate
                    Counter64,
                hwCBQoSIfQueueEnqueuedBytesRate
                    Counter64,
                hwCBQoSIfQueueDiscardedPacketsRate
                    Counter64,
                hwCBQoSIfQueueDiscardedBytesRate
                    Counter64
             }

        hwCBQoSIfQueueMatchedPackets OBJECT-TYPE
            SYNTAX Counter64
            MAX-ACCESS read-only
            STATUS current
            DESCRIPTION
                "Number of packets matched to enqueue."
            ::= { hwCBQoSIfQueueRunInfoEntry 1 }

        
        hwCBQoSIfQueueMatchedBytes OBJECT-TYPE
            SYNTAX Counter64
            MAX-ACCESS read-only
            STATUS current
            DESCRIPTION
                "Number of bytes matched to enqueue."
            ::= { hwCBQoSIfQueueRunInfoEntry 2 }

        
        hwCBQoSIfQueueEnqueuedPackets OBJECT-TYPE
            SYNTAX Counter64
            MAX-ACCESS read-only
            STATUS current
            DESCRIPTION
                "Number of packets enqueued."
            ::= { hwCBQoSIfQueueRunInfoEntry 3 }

        
        hwCBQoSIfQueueEnqueuedBytes OBJECT-TYPE
            SYNTAX Counter64
            MAX-ACCESS read-only
            STATUS current
            DESCRIPTION
                "Number of bytes enqueued."
            ::= { hwCBQoSIfQueueRunInfoEntry 4 }

        
        hwCBQoSIfQueueDiscardedPackets OBJECT-TYPE
            SYNTAX Counter64
            MAX-ACCESS read-only
            STATUS current
            DESCRIPTION
                "Number of packets discarded when enqueued by discard method."
            ::= { hwCBQoSIfQueueRunInfoEntry 5 }

        
        hwCBQoSIfQueueDiscardedBytes OBJECT-TYPE
            SYNTAX Counter64
            MAX-ACCESS read-only
            STATUS current
            DESCRIPTION
                "Number of bytes discarded when enqueued by discard method."
            ::= { hwCBQoSIfQueueRunInfoEntry 6 }

        hwCBQoSIfQueueMatchedPacketsRate OBJECT-TYPE
            SYNTAX Counter64
            MAX-ACCESS read-only
            STATUS current
            DESCRIPTION
                "Rate of packets matched to enqueue."
            ::= { hwCBQoSIfQueueRunInfoEntry 7 }

        
        hwCBQoSIfQueueMatchedBytesRate OBJECT-TYPE
            SYNTAX Counter64
            MAX-ACCESS read-only
            STATUS current
            DESCRIPTION
                "Rate of bytes matched to enqueue."
            ::= { hwCBQoSIfQueueRunInfoEntry 8 }

        
        hwCBQoSIfQueueEnqueuedPacketsRate OBJECT-TYPE
            SYNTAX Counter64
            MAX-ACCESS read-only
            STATUS current
            DESCRIPTION
                "Rate of packets enqueued."
            ::= { hwCBQoSIfQueueRunInfoEntry 9 }

        
        hwCBQoSIfQueueEnqueuedBytesRate OBJECT-TYPE
            SYNTAX Counter64
            MAX-ACCESS read-only
            STATUS current
            DESCRIPTION
                "Rate of bytes enqueued."
            ::= { hwCBQoSIfQueueRunInfoEntry 10 }

        
        hwCBQoSIfQueueDiscardedPacketsRate OBJECT-TYPE
            SYNTAX Counter64
            MAX-ACCESS read-only
            STATUS current
            DESCRIPTION
                "Rate of packets discarded when enqueued by discard method."
            ::= { hwCBQoSIfQueueRunInfoEntry 11 }

        
        hwCBQoSIfQueueDiscardedBytesRate OBJECT-TYPE
            SYNTAX Counter64
            MAX-ACCESS read-only
            STATUS current
            DESCRIPTION
                "Rate of bytes discarded when enqueued by discard method."
            ::= { hwCBQoSIfQueueRunInfoEntry 12 }
        
--  WRED statistics
        hwCBQoSIfWredRunInfoTable OBJECT-TYPE
            SYNTAX SEQUENCE OF HwCBQoSIfWredRunInfoEntry
            MAX-ACCESS not-accessible
            STATUS current
            DESCRIPTION
                "A table of Running statistics for WRED
                in a QoS policy applied on the interface."
            ::= { hwCBQoSIfStaticsObjects 7 }

        
        hwCBQoSIfWredRunInfoEntry OBJECT-TYPE
            SYNTAX HwCBQoSIfWredRunInfoEntry
            MAX-ACCESS not-accessible
            STATUS current
            DESCRIPTION
                "WRED statistics entry."
            INDEX { hwCBQoSIfApplyPolicyIfIndex, hwCBQoSIfApplyPolicyDirection, hwCBQoSPolicyClassIndex, hwCBQoSWredClassValue }
            ::= { hwCBQoSIfWredRunInfoTable 1 }

        
        HwCBQoSIfWredRunInfoEntry ::=
            SEQUENCE { 
                hwCBQoSIfWredRandomDiscardedPackets
                    Counter64,
                hwCBQoSIfWredTailDiscardedPackets
                    Counter64
             }

        hwCBQoSIfWredRandomDiscardedPackets OBJECT-TYPE
            SYNTAX Counter64
            MAX-ACCESS read-only
            STATUS current
            DESCRIPTION
                "Number of packets that random-discarded by WRED."
            ::= { hwCBQoSIfWredRunInfoEntry 1 }

        
        hwCBQoSIfWredTailDiscardedPackets OBJECT-TYPE
            SYNTAX Counter64
            MAX-ACCESS read-only
            STATUS current
            DESCRIPTION
                "Number of packets that tail-discarded by WRED."
            ::= { hwCBQoSIfWredRunInfoEntry 2 }

        
--  LR statistics
        hwCBQoSIfLrRunInfoTable OBJECT-TYPE
            SYNTAX SEQUENCE OF HwCBQoSIfLrRunInfoEntry
            MAX-ACCESS not-accessible
            STATUS current
            DESCRIPTION
                "A table of Running statistics for LR
                in a QoS policy applied on the interface."
            ::= { hwCBQoSIfStaticsObjects 8 }

        
        hwCBQoSIfLrRunInfoEntry OBJECT-TYPE
            SYNTAX HwCBQoSIfLrRunInfoEntry
            MAX-ACCESS not-accessible
            STATUS current
            DESCRIPTION
                "LR statistics entry."
            INDEX { hwCBQoSIfApplyPolicyIfIndex, hwCBQoSIfApplyPolicyDirection, hwCBQoSPolicyClassIndex }
            ::= { hwCBQoSIfLrRunInfoTable 1 }

        
        HwCBQoSIfLrRunInfoEntry ::=
            SEQUENCE { 
                hwCBQoSIfLrPassedPackets
                    Counter64,
                hwCBQoSIfLrPassedBytes
                    Counter64,
                hwCBQoSIfLrDiscardedPackets
                    Counter64,
                hwCBQoSIfLrDiscardedBytes
                    Counter64,
                hwCBQoSIfLrDelayedPackets
                    Counter64,
                hwCBQoSIfLrDelayedBytes
                    Counter64
             }

        hwCBQoSIfLrPassedPackets OBJECT-TYPE
            SYNTAX Counter64
            MAX-ACCESS read-only
            STATUS current
            DESCRIPTION
                "Number of packets passed by LR."
            ::= { hwCBQoSIfLrRunInfoEntry 1 }

        
        hwCBQoSIfLrPassedBytes OBJECT-TYPE
            SYNTAX Counter64
            MAX-ACCESS read-only
            STATUS current
            DESCRIPTION
                "Number of bytes passed by LR."
            ::= { hwCBQoSIfLrRunInfoEntry 2 }

        
        hwCBQoSIfLrDiscardedPackets OBJECT-TYPE
            SYNTAX Counter64
            MAX-ACCESS read-only
            STATUS current
            DESCRIPTION
                "Number of packets discarded by LR."
            ::= { hwCBQoSIfLrRunInfoEntry 3 }

        
        hwCBQoSIfLrDiscardedBytes OBJECT-TYPE
            SYNTAX Counter64
            MAX-ACCESS read-only
            STATUS current
            DESCRIPTION
                "Number of bytes discarded by LR."
            ::= { hwCBQoSIfLrRunInfoEntry 4 }

        
        hwCBQoSIfLrDelayedPackets OBJECT-TYPE
            SYNTAX Counter64
            MAX-ACCESS read-only
            STATUS current
            DESCRIPTION
                "Number of packets delayed by LR."
            ::= { hwCBQoSIfLrRunInfoEntry 5 }

        
        hwCBQoSIfLrDelayedBytes OBJECT-TYPE
            SYNTAX Counter64
            MAX-ACCESS read-only
            STATUS current
            DESCRIPTION
                "Number of bytes delayed by LR."
            ::= { hwCBQoSIfLrRunInfoEntry 6 }

        
--  Redirect statistics
        hwCBQoSIfRedirectRunInfoTable OBJECT-TYPE
            SYNTAX SEQUENCE OF HwCBQoSIfRedirectRunInfoEntry
            MAX-ACCESS not-accessible
            STATUS current
            DESCRIPTION
                "A table of Running statistics for redirect
                in a QoS policy applied on the interface."
            ::= { hwCBQoSIfStaticsObjects 9 }

        
        hwCBQoSIfRedirectRunInfoEntry OBJECT-TYPE
            SYNTAX HwCBQoSIfRedirectRunInfoEntry
            MAX-ACCESS not-accessible
            STATUS current
            DESCRIPTION
                "Redirect statistics entry."
            INDEX { hwCBQoSIfApplyPolicyIfIndex, hwCBQoSIfApplyPolicyDirection, hwCBQoSPolicyClassIndex }
            ::= { hwCBQoSIfRedirectRunInfoTable 1 }

        
        HwCBQoSIfRedirectRunInfoEntry ::=
            SEQUENCE { 
                hwCBQoSIfRedirectedPackets
                    Counter64,
                hwCBQoSIfRedirectedBytes
                    Counter64
             }

        hwCBQoSIfRedirectedPackets OBJECT-TYPE
            SYNTAX Counter64
            MAX-ACCESS read-only
            STATUS current
            DESCRIPTION
                "Number of packets Redirected."
            ::= { hwCBQoSIfRedirectRunInfoEntry 1 }

        
        hwCBQoSIfRedirectedBytes OBJECT-TYPE
            SYNTAX Counter64
            MAX-ACCESS read-only
            STATUS current
            DESCRIPTION
                "Number of bytes Redirected."
            ::= { hwCBQoSIfRedirectRunInfoEntry 2 }

        
--  Firewall statistics
        hwCBQoSIfFirewallRunInfoTable OBJECT-TYPE
            SYNTAX SEQUENCE OF HwCBQoSIfFirewallRunInfoEntry
            MAX-ACCESS not-accessible
            STATUS current
            DESCRIPTION
                "A table of Running statistics for fire wall
                in a QoS policy applied on the interface."
            ::= { hwCBQoSIfStaticsObjects 10 }

        
        hwCBQoSIfFirewallRunInfoEntry OBJECT-TYPE
            SYNTAX HwCBQoSIfFirewallRunInfoEntry
            MAX-ACCESS not-accessible
            STATUS current
            DESCRIPTION
                "Fire wall statistics entry."
            INDEX { hwCBQoSIfApplyPolicyIfIndex, hwCBQoSIfApplyPolicyDirection, hwCBQoSPolicyClassIndex }
            ::= { hwCBQoSIfFirewallRunInfoTable 1 }

        
        HwCBQoSIfFirewallRunInfoEntry ::=
            SEQUENCE { 
                hwCBQoSIfFilteredPackets
                    Counter64,
                hwCBQoSIfFilteredBytes
                    Counter64
             }

        hwCBQoSIfFilteredPackets OBJECT-TYPE
            SYNTAX Counter64
            MAX-ACCESS read-only
            STATUS current
            DESCRIPTION
                "Number of packets Filtered."
            ::= { hwCBQoSIfFirewallRunInfoEntry 1 }

        
        hwCBQoSIfFilteredBytes OBJECT-TYPE
            SYNTAX Counter64
            MAX-ACCESS read-only
            STATUS current
            DESCRIPTION
                "Number of bytes Filtered."
            ::= { hwCBQoSIfFirewallRunInfoEntry 2 }

        
--  Mirror statistics
        hwCBQoSIfMirrorRunInfoTable OBJECT-TYPE
            SYNTAX SEQUENCE OF HwCBQoSIfMirrorRunInfoEntry
            MAX-ACCESS not-accessible
            STATUS current
            DESCRIPTION
                "A table of Running statistics for mirror
                in a QoS policy applied on the interface."
            ::= { hwCBQoSIfStaticsObjects 11 }

        
        hwCBQoSIfMirrorRunInfoEntry OBJECT-TYPE
            SYNTAX HwCBQoSIfMirrorRunInfoEntry
            MAX-ACCESS not-accessible
            STATUS current
            DESCRIPTION
                "Mirror statistics entry."
            INDEX { hwCBQoSIfApplyPolicyIfIndex, hwCBQoSIfApplyPolicyDirection, hwCBQoSPolicyClassIndex }
            ::= { hwCBQoSIfMirrorRunInfoTable 1 }

        
        HwCBQoSIfMirrorRunInfoEntry ::=
            SEQUENCE { 
                hwCBQoSIfMirroredPackets
                    Counter64,
                hwCBQoSIfMirroredBytes
                    Counter64
             }

        hwCBQoSIfMirroredPackets OBJECT-TYPE
            SYNTAX Counter64
            MAX-ACCESS read-only
            STATUS current
            DESCRIPTION
                "Number of packets Mirrored."
            ::= { hwCBQoSIfMirrorRunInfoEntry 1 }

        
        hwCBQoSIfMirroredBytes OBJECT-TYPE
            SYNTAX Counter64
            MAX-ACCESS read-only
            STATUS current
            DESCRIPTION
                "Number of bytes Mirrored."
            ::= { hwCBQoSIfMirrorRunInfoEntry 2 }

        
--  Urpf statistics
        hwCBQoSIfUrpfRunInfoTable OBJECT-TYPE
            SYNTAX SEQUENCE OF HwCBQoSIfUrpfRunInfoEntry
            MAX-ACCESS not-accessible
            STATUS current
            DESCRIPTION
                "A table of Running statistics for urpf
                in a QoS policy applied on the interface."
            ::= { hwCBQoSIfStaticsObjects 12 }

        
        hwCBQoSIfUrpfRunInfoEntry OBJECT-TYPE
            SYNTAX HwCBQoSIfUrpfRunInfoEntry
            MAX-ACCESS not-accessible
            STATUS current
            DESCRIPTION
                "Urpf statistics entry."
            INDEX { hwCBQoSIfApplyPolicyIfIndex, hwCBQoSIfApplyPolicyDirection, hwCBQoSPolicyClassIndex }
            ::= { hwCBQoSIfUrpfRunInfoTable 1 }

        
        HwCBQoSIfUrpfRunInfoEntry ::=
            SEQUENCE { 
                hwCBQoSIfUrpfPassedPackets
                    Counter64,
                hwCBQoSIfUrpfPassedBytes
                    Counter64,
                hwCBQoSIfUrpfDroppedPackets
                    Counter64,
                hwCBQoSIfUrpfDroppedBytes
                    Counter64
             }

        hwCBQoSIfUrpfPassedPackets OBJECT-TYPE
            SYNTAX Counter64
            MAX-ACCESS read-only
            STATUS current
            DESCRIPTION
                "Number of packets passed."
            ::= { hwCBQoSIfUrpfRunInfoEntry 1 }

        
        hwCBQoSIfUrpfPassedBytes OBJECT-TYPE
            SYNTAX Counter64
            MAX-ACCESS read-only
            STATUS current
            DESCRIPTION
                "Number of bytes passed."
            ::= { hwCBQoSIfUrpfRunInfoEntry 2 }

        
        hwCBQoSIfUrpfDroppedPackets OBJECT-TYPE
            SYNTAX Counter64
            MAX-ACCESS read-only
            STATUS current
            DESCRIPTION
                "Number of packets dropped."
            ::= { hwCBQoSIfUrpfRunInfoEntry 3 }

        
        hwCBQoSIfUrpfDroppedBytes OBJECT-TYPE
            SYNTAX Counter64
            MAX-ACCESS read-only
            STATUS current
            DESCRIPTION
                "Number of bytes dropped."
            ::= { hwCBQoSIfUrpfRunInfoEntry 4 }

        
--  Sample statistics
        hwCBQoSIfSampleRunInfoTable OBJECT-TYPE
            SYNTAX SEQUENCE OF HwCBQoSIfSampleRunInfoEntry
            MAX-ACCESS not-accessible
            STATUS current
            DESCRIPTION
                "A table of Running statistics for sample
                in a QoS policy applied on the interface."
            ::= { hwCBQoSIfStaticsObjects 13 }

        
        hwCBQoSIfSampleRunInfoEntry OBJECT-TYPE
            SYNTAX HwCBQoSIfSampleRunInfoEntry
            MAX-ACCESS not-accessible
            STATUS current
            DESCRIPTION
                "Sample statistics entry."
            INDEX { hwCBQoSIfApplyPolicyIfIndex, hwCBQoSIfApplyPolicyDirection, hwCBQoSPolicyClassIndex }
            ::= { hwCBQoSIfSampleRunInfoTable 1 }

        
        HwCBQoSIfSampleRunInfoEntry ::=
            SEQUENCE { 
                hwCBQoSIfSampledPackets
                    Counter64,
                hwCBQoSIfSampledBytes
                    Counter64
             }

        hwCBQoSIfSampledPackets OBJECT-TYPE
            SYNTAX Counter64
            MAX-ACCESS read-only
            STATUS current
            DESCRIPTION
                "Number of packets Sampled."
            ::= { hwCBQoSIfSampleRunInfoEntry 1 }

        
        hwCBQoSIfSampledBytes OBJECT-TYPE
            SYNTAX Counter64
            MAX-ACCESS read-only
            STATUS current
            DESCRIPTION
                "Number of bytes Sampled."
            ::= { hwCBQoSIfSampleRunInfoEntry 2 }

        
--  ATM Interface PVC: policy Running statistics information
        hwCBQoSAtmPvcStaticsObjects OBJECT IDENTIFIER ::= { hwCBQoSApplyPolicyStaticsObjects 2 }

        
--  ATM PVC CBQ statistics
        hwCBQoSAtmPvcCbqRunInfoTable OBJECT-TYPE
            SYNTAX SEQUENCE OF HwCBQoSAtmPvcCbqRunInfoEntry
            MAX-ACCESS not-accessible
            STATUS current
            DESCRIPTION
                "A table of atm pvc CBQ Running statistics. When policy using queue behavior is applied on
                atm pvc atm pvc will using Class Based Queuing."
            ::= { hwCBQoSAtmPvcStaticsObjects 1 }

        
        hwCBQoSAtmPvcCbqRunInfoEntry OBJECT-TYPE
            SYNTAX HwCBQoSAtmPvcCbqRunInfoEntry
            MAX-ACCESS not-accessible
            STATUS current
            DESCRIPTION
                "FR PVC CBQ statistics entry."
            INDEX { hwCBQoSAtmPvcApplyPolicyIfIndex, hwCBQoSAtmPvcApplyPolicyVPI, hwCBQoSAtmPvcApplyPolicyVCI }
            ::= { hwCBQoSAtmPvcCbqRunInfoTable 1 }

        
        HwCBQoSAtmPvcCbqRunInfoEntry ::=
            SEQUENCE { 
                hwCBQoSAtmPvcCbqQueueSize
                    Integer32,
                hwCBQoSAtmPvcCbqDiscard
                    Counter64,
                hwCBQoSAtmPvcCbqEfQueueSize
                    Integer32,
                hwCBQoSAtmPvcCbqAfQueueSize
                    Integer32,
                hwCBQoSAtmPvcCbqBeQueueSize
                    Integer32,
                hwCBQoSAtmPvcCbqBeActiveQueueNum
                    Integer32,
                hwCBQoSAtmPvcCbqBeMaxActiveQueueNum
                    Integer32,
                hwCBQoSAtmPvcCbqBeTotalQueueNum
                    Integer32,
                hwCBQoSAtmPvcCbqAfAllocatedQueueNum
                    Integer32
             }

        hwCBQoSAtmPvcCbqQueueSize OBJECT-TYPE
            SYNTAX Integer32
            MAX-ACCESS read-only
            STATUS current
            DESCRIPTION
                "Queue size of CBQ"
            ::= { hwCBQoSAtmPvcCbqRunInfoEntry 1 }

        
        hwCBQoSAtmPvcCbqDiscard OBJECT-TYPE
            SYNTAX Counter64
            MAX-ACCESS read-only
            STATUS current
            DESCRIPTION
                "The number of discarded packets which coundn't be enqueued."
            ::= { hwCBQoSAtmPvcCbqRunInfoEntry 2 }

        
        hwCBQoSAtmPvcCbqEfQueueSize OBJECT-TYPE
            SYNTAX Integer32
            MAX-ACCESS read-only
            STATUS current
            DESCRIPTION
                "Queue size of EF"
            ::= { hwCBQoSAtmPvcCbqRunInfoEntry 3 }

        
        hwCBQoSAtmPvcCbqAfQueueSize OBJECT-TYPE
            SYNTAX Integer32
            MAX-ACCESS read-only
            STATUS current
            DESCRIPTION
                "Queue size of AF"
            ::= { hwCBQoSAtmPvcCbqRunInfoEntry 4 }

        
        hwCBQoSAtmPvcCbqBeQueueSize OBJECT-TYPE
            SYNTAX Integer32
            MAX-ACCESS read-only
            STATUS current
            DESCRIPTION
                "Queue size of BE"
            ::= { hwCBQoSAtmPvcCbqRunInfoEntry 5 }

        
        hwCBQoSAtmPvcCbqBeActiveQueueNum OBJECT-TYPE
            SYNTAX Integer32
            MAX-ACCESS read-only
            STATUS current
            DESCRIPTION
                "the number of Active Be Queue"
            ::= { hwCBQoSAtmPvcCbqRunInfoEntry 6 }

        
        hwCBQoSAtmPvcCbqBeMaxActiveQueueNum OBJECT-TYPE
            SYNTAX Integer32
            MAX-ACCESS read-only
            STATUS current
            DESCRIPTION
                "the max number of Active Be Queue"
            ::= { hwCBQoSAtmPvcCbqRunInfoEntry 7 }

        
        hwCBQoSAtmPvcCbqBeTotalQueueNum OBJECT-TYPE
            SYNTAX Integer32
            MAX-ACCESS read-only
            STATUS current
            DESCRIPTION
                "the total number of Be Queue"
            ::= { hwCBQoSAtmPvcCbqRunInfoEntry 8 }

        
        hwCBQoSAtmPvcCbqAfAllocatedQueueNum OBJECT-TYPE
            SYNTAX Integer32
            MAX-ACCESS read-only
            STATUS current
            DESCRIPTION
                "the Allocated number of Af Queue"
            ::= { hwCBQoSAtmPvcCbqRunInfoEntry 9 }

        
--  Class match statistics
        hwCBQoSAtmPvcClassMatchRunInfoTable OBJECT-TYPE
            SYNTAX SEQUENCE OF HwCBQoSAtmPvcClassMatchRunInfoEntry
            MAX-ACCESS not-accessible
            STATUS current
            DESCRIPTION
                "A table of Running statistics for matching a classifier
                in a QoS policy applied on ATM PVC."
            ::= { hwCBQoSAtmPvcStaticsObjects 2 }

        
        hwCBQoSAtmPvcClassMatchRunInfoEntry OBJECT-TYPE
            SYNTAX HwCBQoSAtmPvcClassMatchRunInfoEntry
            MAX-ACCESS not-accessible
            STATUS current
            DESCRIPTION
                "Classifier matching statistics entry."
            INDEX { hwCBQoSAtmPvcApplyPolicyIfIndex, hwCBQoSAtmPvcApplyPolicyVPI, hwCBQoSAtmPvcApplyPolicyVCI, hwCBQoSAtmPvcApplyPolicyDirection, hwCBQoSPolicyClassIndex
                 }
            ::= { hwCBQoSAtmPvcClassMatchRunInfoTable 1 }

        
        HwCBQoSAtmPvcClassMatchRunInfoEntry ::=
            SEQUENCE { 
                hwCBQoSAtmPvcClassMatchPackets
                    Counter64,
                hwCBQoSAtmPvcClassMatchBytes
                    Counter64,
                hwCBQoSAtmPvcClassAverageRate
                    Counter64
             }

        hwCBQoSAtmPvcClassMatchPackets OBJECT-TYPE
            SYNTAX Counter64
            MAX-ACCESS read-only
            STATUS current
            DESCRIPTION
                "Number of packets matching a class in a QoS policy."
            ::= { hwCBQoSAtmPvcClassMatchRunInfoEntry 1 }

        
        hwCBQoSAtmPvcClassMatchBytes OBJECT-TYPE
            SYNTAX Counter64
            MAX-ACCESS read-only
            STATUS current
            DESCRIPTION
                "Number of bytes matching a class in a QoS policy."
            ::= { hwCBQoSAtmPvcClassMatchRunInfoEntry 2 }

        
        hwCBQoSAtmPvcClassAverageRate OBJECT-TYPE
            SYNTAX Counter64
            MAX-ACCESS read-only
            STATUS current
            DESCRIPTION
                "Average rate of the traffic matching a class in a QoS policy.
                For inbound QoS policy, it is the rate of the traffic input;
                For outbound QoS policy, it is the rate of the traffic output.
                Only software QoS support this node."
            ::= { hwCBQoSAtmPvcClassMatchRunInfoEntry 3 }

        
--  CAR statistics
        hwCBQoSAtmPvcCarRunInfoTable OBJECT-TYPE
            SYNTAX SEQUENCE OF HwCBQoSAtmPvcCarRunInfoEntry
            MAX-ACCESS not-accessible
            STATUS current
            DESCRIPTION
                "A table of Running statistics for CAR
                in a QoS policy applied on ATM PVC."
            ::= { hwCBQoSAtmPvcStaticsObjects 3 }

        
        hwCBQoSAtmPvcCarRunInfoEntry OBJECT-TYPE
            SYNTAX HwCBQoSAtmPvcCarRunInfoEntry
            MAX-ACCESS not-accessible
            STATUS current
            DESCRIPTION
                "CAR statistics entry."
            INDEX { hwCBQoSAtmPvcApplyPolicyIfIndex, hwCBQoSAtmPvcApplyPolicyVPI, hwCBQoSAtmPvcApplyPolicyVCI, hwCBQoSAtmPvcApplyPolicyDirection, hwCBQoSPolicyClassIndex
                 }
            ::= { hwCBQoSAtmPvcCarRunInfoTable 1 }

        
        HwCBQoSAtmPvcCarRunInfoEntry ::=
            SEQUENCE { 
                hwCBQoSAtmPvcCarConformPackets
                    Counter64,
                hwCBQoSAtmPvcCarConformBytes
                    Counter64,
                hwCBQoSAtmPvcCarExceedPackets
                    Counter64,
                hwCBQoSAtmPvcCarExceedBytes
                    Counter64,
                hwCBQoSAtmPvcCarConformPacketsRate
                    Counter64,
                hwCBQoSAtmPvcCarConformBytesRate
                    Counter64,
                hwCBQoSAtmPvcCarExceedPacketsRate
                    Counter64,
                hwCBQoSAtmPvcCarExceedBytesRate
                    Counter64
             }

        hwCBQoSAtmPvcCarConformPackets OBJECT-TYPE
            SYNTAX Counter64
            MAX-ACCESS read-only
            STATUS current
            DESCRIPTION
                "Number of packets that conforming specified CIR."
            ::= { hwCBQoSAtmPvcCarRunInfoEntry 1 }

        
        hwCBQoSAtmPvcCarConformBytes OBJECT-TYPE
            SYNTAX Counter64
            MAX-ACCESS read-only
            STATUS current
            DESCRIPTION
                "Number of bytes that conforming specified CIR."
            ::= { hwCBQoSAtmPvcCarRunInfoEntry 2 }

        
        hwCBQoSAtmPvcCarExceedPackets OBJECT-TYPE
            SYNTAX Counter64
            MAX-ACCESS read-only
            STATUS current
            DESCRIPTION
                "Number of packets exceeded CIR."
            ::= { hwCBQoSAtmPvcCarRunInfoEntry 3 }

        
        hwCBQoSAtmPvcCarExceedBytes OBJECT-TYPE
            SYNTAX Counter64
            MAX-ACCESS read-only
            STATUS current
            DESCRIPTION
                "Number of bytes exceeded CIR."
            ::= { hwCBQoSAtmPvcCarRunInfoEntry 4 }

        hwCBQoSAtmPvcCarConformPacketsRate OBJECT-TYPE
            SYNTAX Counter64
            MAX-ACCESS read-only
            STATUS current
            DESCRIPTION
                "Rate of packets that conforming specified CIR."
            ::= { hwCBQoSAtmPvcCarRunInfoEntry 5 }

        
        hwCBQoSAtmPvcCarConformBytesRate OBJECT-TYPE
            SYNTAX Counter64
            MAX-ACCESS read-only
            STATUS current
            DESCRIPTION
                "Rate of bytes that conforming specified CIR."
            ::= { hwCBQoSAtmPvcCarRunInfoEntry 6 }

        
        hwCBQoSAtmPvcCarExceedPacketsRate OBJECT-TYPE
            SYNTAX Counter64
            MAX-ACCESS read-only
            STATUS current
            DESCRIPTION
                "Rate of packets exceeded CIR."
            ::= { hwCBQoSAtmPvcCarRunInfoEntry 7 }

        
        hwCBQoSAtmPvcCarExceedBytesRate OBJECT-TYPE
            SYNTAX Counter64
            MAX-ACCESS read-only
            STATUS current
            DESCRIPTION
                "Rate of bytes exceeded CIR."
            ::= { hwCBQoSAtmPvcCarRunInfoEntry 8 }
        
--  GTS statistics
        hwCBQoSAtmPvcGtsRunInfoTable OBJECT-TYPE
            SYNTAX SEQUENCE OF HwCBQoSAtmPvcGtsRunInfoEntry
            MAX-ACCESS not-accessible
            STATUS current
            DESCRIPTION
                "A table of Running statistics for GTS
                in a QoS policy applied on ATM PVC."
            ::= { hwCBQoSAtmPvcStaticsObjects 4 }

        
        hwCBQoSAtmPvcGtsRunInfoEntry OBJECT-TYPE
            SYNTAX HwCBQoSAtmPvcGtsRunInfoEntry
            MAX-ACCESS not-accessible
            STATUS current
            DESCRIPTION
                "GTS statistics entry."
            INDEX { hwCBQoSAtmPvcApplyPolicyIfIndex, hwCBQoSAtmPvcApplyPolicyVPI, hwCBQoSAtmPvcApplyPolicyVCI, hwCBQoSAtmPvcApplyPolicyDirection, hwCBQoSPolicyClassIndex
                 }
            ::= { hwCBQoSAtmPvcGtsRunInfoTable 1 }

        
        HwCBQoSAtmPvcGtsRunInfoEntry ::=
            SEQUENCE { 
                hwCBQoSAtmPvcGtsPassedPackets
                    Counter64,
                hwCBQoSAtmPvcGtsPassedBytes
                    Counter64,
                hwCBQoSAtmPvcGtsDiscardedPackets
                    Counter64,
                hwCBQoSAtmPvcGtsDiscardedBytes
                    Counter64,
                hwCBQoSAtmPvcGtsDelayedPackets
                    Counter64,
                hwCBQoSAtmPvcGtsDelayedBytes
                    Counter64,
                hwCBQoSAtmPvcGtsQueueSize
                    Integer32
             }

        hwCBQoSAtmPvcGtsPassedPackets OBJECT-TYPE
            SYNTAX Counter64
            MAX-ACCESS read-only
            STATUS current
            DESCRIPTION
                "Number of packets passed by GTS."
            ::= { hwCBQoSAtmPvcGtsRunInfoEntry 1 }

        
        hwCBQoSAtmPvcGtsPassedBytes OBJECT-TYPE
            SYNTAX Counter64
            MAX-ACCESS read-only
            STATUS current
            DESCRIPTION
                "Number of bytes passed by GTS."
            ::= { hwCBQoSAtmPvcGtsRunInfoEntry 2 }

        
        hwCBQoSAtmPvcGtsDiscardedPackets OBJECT-TYPE
            SYNTAX Counter64
            MAX-ACCESS read-only
            STATUS current
            DESCRIPTION
                "Number of packets discarded by GTS."
            ::= { hwCBQoSAtmPvcGtsRunInfoEntry 3 }

        
        hwCBQoSAtmPvcGtsDiscardedBytes OBJECT-TYPE
            SYNTAX Counter64
            MAX-ACCESS read-only
            STATUS current
            DESCRIPTION
                "Number of bytes discarded by GTS."
            ::= { hwCBQoSAtmPvcGtsRunInfoEntry 4 }

        
        hwCBQoSAtmPvcGtsDelayedPackets OBJECT-TYPE
            SYNTAX Counter64
            MAX-ACCESS read-only
            STATUS current
            DESCRIPTION
                "Number of packets delayed by GTS."
            ::= { hwCBQoSAtmPvcGtsRunInfoEntry 5 }

        
        hwCBQoSAtmPvcGtsDelayedBytes OBJECT-TYPE
            SYNTAX Counter64
            MAX-ACCESS read-only
            STATUS current
            DESCRIPTION
                "Number of bytes delayed by GTS."
            ::= { hwCBQoSAtmPvcGtsRunInfoEntry 6 }

        
        hwCBQoSAtmPvcGtsQueueSize OBJECT-TYPE
            SYNTAX Integer32
            MAX-ACCESS read-only
            STATUS current
            DESCRIPTION
                "Queue size of GTS queue."
            ::= { hwCBQoSAtmPvcGtsRunInfoEntry 7 }

        
--  Remark statistics
        hwCBQoSAtmPvcRemarkRunInfoTable OBJECT-TYPE
            SYNTAX SEQUENCE OF HwCBQoSAtmPvcRemarkRunInfoEntry
            MAX-ACCESS not-accessible
            STATUS current
            DESCRIPTION
                "A table of Running statistics for remarking
                in a QoS policy applied on ATM PVC."
            ::= { hwCBQoSAtmPvcStaticsObjects 5 }

        
        hwCBQoSAtmPvcRemarkRunInfoEntry OBJECT-TYPE
            SYNTAX HwCBQoSAtmPvcRemarkRunInfoEntry
            MAX-ACCESS not-accessible
            STATUS current
            DESCRIPTION
                "Remarking statistics entry."
            INDEX { hwCBQoSAtmPvcApplyPolicyIfIndex, hwCBQoSAtmPvcApplyPolicyVPI, hwCBQoSAtmPvcApplyPolicyVCI, hwCBQoSAtmPvcApplyPolicyDirection, hwCBQoSPolicyClassIndex
                 }
            ::= { hwCBQoSAtmPvcRemarkRunInfoTable 1 }

        
        HwCBQoSAtmPvcRemarkRunInfoEntry ::=
            SEQUENCE { 
                hwCBQoSAtmPvcRemarkedPackets
                    Counter64
             }

        hwCBQoSAtmPvcRemarkedPackets OBJECT-TYPE
            SYNTAX Counter64
            MAX-ACCESS read-only
            STATUS current
            DESCRIPTION
                "Number of packets remarked."
            ::= { hwCBQoSAtmPvcRemarkRunInfoEntry 1 }

        
--  Queue statistics
        hwCBQoSAtmPvcQueueRunInfoTable OBJECT-TYPE
            SYNTAX SEQUENCE OF HwCBQoSAtmPvcQueueRunInfoEntry
            MAX-ACCESS not-accessible
            STATUS current
            DESCRIPTION
                "A table of Running statistics for queue
                in a QoS policy applied on ATM PVC."
            ::= { hwCBQoSAtmPvcStaticsObjects 6 }

        
        hwCBQoSAtmPvcQueueRunInfoEntry OBJECT-TYPE
            SYNTAX HwCBQoSAtmPvcQueueRunInfoEntry
            MAX-ACCESS not-accessible
            STATUS current
            DESCRIPTION
                "Queue statistics entry."
            INDEX { hwCBQoSAtmPvcApplyPolicyIfIndex, hwCBQoSAtmPvcApplyPolicyVPI, hwCBQoSAtmPvcApplyPolicyVCI, hwCBQoSAtmPvcApplyPolicyDirection, hwCBQoSPolicyClassIndex
                 }
            ::= { hwCBQoSAtmPvcQueueRunInfoTable 1 }

        
        HwCBQoSAtmPvcQueueRunInfoEntry ::=
            SEQUENCE { 
                hwCBQoSAtmPvcQueueMatchedPackets
                    Counter64,
                hwCBQoSAtmPvcQueueMatchedBytes
                    Counter64,
                hwCBQoSAtmPvcQueueEnqueuedPackets
                    Counter64,
                hwCBQoSAtmPvcQueueEnqueuedBytes
                    Counter64,
                hwCBQoSAtmPvcQueueDiscardedPackets
                    Counter64,
                hwCBQoSAtmPvcQueueDiscardedBytes
                    Counter64,
                hwCBQoSAtmPvcQueueMatchedPacketsRate
                    Counter64,
                hwCBQoSAtmPvcQueueMatchedBytesRate
                    Counter64,
                hwCBQoSAtmPvcQueueEnqueuedPacketsRate
                    Counter64,
                hwCBQoSAtmPvcQueueEnqueuedBytesRate
                    Counter64,
                hwCBQoSAtmPvcQueueDiscardedPacketsRate
                    Counter64,
                hwCBQoSAtmPvcQueueDiscardedBytesRate
                    Counter64
             }

        hwCBQoSAtmPvcQueueMatchedPackets OBJECT-TYPE
            SYNTAX Counter64
            MAX-ACCESS read-only
            STATUS current
            DESCRIPTION
                "Number of packets matched to enqueue."
            ::= { hwCBQoSAtmPvcQueueRunInfoEntry 1 }

        
        hwCBQoSAtmPvcQueueMatchedBytes OBJECT-TYPE
            SYNTAX Counter64
            MAX-ACCESS read-only
            STATUS current
            DESCRIPTION
                "Number of bytes matched to enqueue."
            ::= { hwCBQoSAtmPvcQueueRunInfoEntry 2 }

        
        hwCBQoSAtmPvcQueueEnqueuedPackets OBJECT-TYPE
            SYNTAX Counter64
            MAX-ACCESS read-only
            STATUS current
            DESCRIPTION
                "Number of packets enqueued."
            ::= { hwCBQoSAtmPvcQueueRunInfoEntry 3 }

        
        hwCBQoSAtmPvcQueueEnqueuedBytes OBJECT-TYPE
            SYNTAX Counter64
            MAX-ACCESS read-only
            STATUS current
            DESCRIPTION
                "Number of bytes enqueued."
            ::= { hwCBQoSAtmPvcQueueRunInfoEntry 4 }

        
        hwCBQoSAtmPvcQueueDiscardedPackets OBJECT-TYPE
            SYNTAX Counter64
            MAX-ACCESS read-only
            STATUS current
            DESCRIPTION
                "Number of packets discard when enqueued by discard method."
            ::= { hwCBQoSAtmPvcQueueRunInfoEntry 5 }

        
        hwCBQoSAtmPvcQueueDiscardedBytes OBJECT-TYPE
            SYNTAX Counter64
            MAX-ACCESS read-only
            STATUS current
            DESCRIPTION
                "Number of bytes discard when enqueued by discard method."
            ::= { hwCBQoSAtmPvcQueueRunInfoEntry 6 }

        hwCBQoSAtmPvcQueueMatchedPacketsRate OBJECT-TYPE
            SYNTAX Counter64
            MAX-ACCESS read-only
            STATUS current
            DESCRIPTION
                "Rate of packets matched to enqueue."
            ::= { hwCBQoSAtmPvcQueueRunInfoEntry 7 }

        
        hwCBQoSAtmPvcQueueMatchedBytesRate OBJECT-TYPE
            SYNTAX Counter64
            MAX-ACCESS read-only
            STATUS current
            DESCRIPTION
                "Rate of bytes matched to enqueue."
            ::= { hwCBQoSAtmPvcQueueRunInfoEntry 8 }

        
        hwCBQoSAtmPvcQueueEnqueuedPacketsRate OBJECT-TYPE
            SYNTAX Counter64
            MAX-ACCESS read-only
            STATUS current
            DESCRIPTION
                "Rate of packets enqueued."
            ::= { hwCBQoSAtmPvcQueueRunInfoEntry 9 }

        
        hwCBQoSAtmPvcQueueEnqueuedBytesRate OBJECT-TYPE
            SYNTAX Counter64
            MAX-ACCESS read-only
            STATUS current
            DESCRIPTION
                "Rate of bytes enqueued."
            ::= { hwCBQoSAtmPvcQueueRunInfoEntry 10 }

        
        hwCBQoSAtmPvcQueueDiscardedPacketsRate OBJECT-TYPE
            SYNTAX Counter64
            MAX-ACCESS read-only
            STATUS current
            DESCRIPTION
                "Rate of packets discard when enqueued by discard method."
            ::= { hwCBQoSAtmPvcQueueRunInfoEntry 11 }

        
        hwCBQoSAtmPvcQueueDiscardedBytesRate OBJECT-TYPE
            SYNTAX Counter64
            MAX-ACCESS read-only
            STATUS current
            DESCRIPTION
                "Rate of bytes discard when enqueued by discard method."
            ::= { hwCBQoSAtmPvcQueueRunInfoEntry 12 }
        
--  WRED statistics
        hwCBQoSAtmPvcWredRunInfoTable OBJECT-TYPE
            SYNTAX SEQUENCE OF HwCBQoSAtmPvcWredRunInfoEntry
            MAX-ACCESS not-accessible
            STATUS current
            DESCRIPTION
                "A table of Running statistics for WRED
                in a QoS policy applied on ATM PVC."
            ::= { hwCBQoSAtmPvcStaticsObjects 7 }

        
        hwCBQoSAtmPvcWredRunInfoEntry OBJECT-TYPE
            SYNTAX HwCBQoSAtmPvcWredRunInfoEntry
            MAX-ACCESS not-accessible
            STATUS current
            DESCRIPTION
                "WRED statistics entry."
            INDEX { hwCBQoSAtmPvcApplyPolicyIfIndex, hwCBQoSAtmPvcApplyPolicyVPI, hwCBQoSAtmPvcApplyPolicyVCI, hwCBQoSAtmPvcApplyPolicyDirection, hwCBQoSPolicyClassIndex, 
                hwCBQoSWredClassValue }
            ::= { hwCBQoSAtmPvcWredRunInfoTable 1 }

        
        HwCBQoSAtmPvcWredRunInfoEntry ::=
            SEQUENCE { 
                hwCBQoSAtmPvcWredRandomDiscardedPackets
                    Counter64,
                hwCBQoSAtmPvcWredTailDiscardedPackets
                    Counter64
             }

        hwCBQoSAtmPvcWredRandomDiscardedPackets OBJECT-TYPE
            SYNTAX Counter64
            MAX-ACCESS read-only
            STATUS current
            DESCRIPTION
                "Number of packets randomly discarded by WRED."
            ::= { hwCBQoSAtmPvcWredRunInfoEntry 1 }

        
        hwCBQoSAtmPvcWredTailDiscardedPackets OBJECT-TYPE
            SYNTAX Counter64
            MAX-ACCESS read-only
            STATUS current
            DESCRIPTION
                "Number of packets tail-discarded by WRED."
            ::= { hwCBQoSAtmPvcWredRunInfoEntry 2 }

        
--  LR statistics
        hwCBQoSAtmPvcLrRunInfoTable OBJECT-TYPE
            SYNTAX SEQUENCE OF HwCBQoSAtmPvcLrRunInfoEntry
            MAX-ACCESS not-accessible
            STATUS current
            DESCRIPTION
                "A table of Running statistics for LR
                in a QoS policy applied on ATM PVC."
            ::= { hwCBQoSAtmPvcStaticsObjects 8 }

        
        hwCBQoSAtmPvcLrRunInfoEntry OBJECT-TYPE
            SYNTAX HwCBQoSAtmPvcLrRunInfoEntry
            MAX-ACCESS not-accessible
            STATUS current
            DESCRIPTION
                "LR statistics entry."
            INDEX { hwCBQoSAtmPvcApplyPolicyIfIndex, hwCBQoSAtmPvcApplyPolicyVPI, hwCBQoSAtmPvcApplyPolicyVCI, hwCBQoSAtmPvcApplyPolicyDirection, hwCBQoSPolicyClassIndex
                 }
            ::= { hwCBQoSAtmPvcLrRunInfoTable 1 }

        
        HwCBQoSAtmPvcLrRunInfoEntry ::=
            SEQUENCE { 
                hwCBQoSAtmPvcLrPassedPackets
                    Counter64,
                hwCBQoSAtmPvcLrPassedBytes
                    Counter64,
                hwCBQoSAtmPvcLrDiscardedPackets
                    Counter64,
                hwCBQoSAtmPvcLrDiscardedBytes
                    Counter64,
                hwCBQoSAtmPvcLrDelayedPackets
                    Counter64,
                hwCBQoSAtmPvcLrDelayedBytes
                    Counter64
             }

        hwCBQoSAtmPvcLrPassedPackets OBJECT-TYPE
            SYNTAX Counter64
            MAX-ACCESS read-only
            STATUS current
            DESCRIPTION
                "Number of packets passed by LR."
            ::= { hwCBQoSAtmPvcLrRunInfoEntry 1 }

        
        hwCBQoSAtmPvcLrPassedBytes OBJECT-TYPE
            SYNTAX Counter64
            MAX-ACCESS read-only
            STATUS current
            DESCRIPTION
                "Number of bytes passed by LR."
            ::= { hwCBQoSAtmPvcLrRunInfoEntry 2 }

        
        hwCBQoSAtmPvcLrDiscardedPackets OBJECT-TYPE
            SYNTAX Counter64
            MAX-ACCESS read-only
            STATUS current
            DESCRIPTION
                "Number of packets discarded by LR."
            ::= { hwCBQoSAtmPvcLrRunInfoEntry 3 }

        
        hwCBQoSAtmPvcLrDiscardedBytes OBJECT-TYPE
            SYNTAX Counter64
            MAX-ACCESS read-only
            STATUS current
            DESCRIPTION
                "Number of bytes discarded by LR."
            ::= { hwCBQoSAtmPvcLrRunInfoEntry 4 }

        
        hwCBQoSAtmPvcLrDelayedPackets OBJECT-TYPE
            SYNTAX Counter64
            MAX-ACCESS read-only
            STATUS current
            DESCRIPTION
                "Number of packets delayed by LR."
            ::= { hwCBQoSAtmPvcLrRunInfoEntry 5 }

        
        hwCBQoSAtmPvcLrDelayedBytes OBJECT-TYPE
            SYNTAX Counter64
            MAX-ACCESS read-only
            STATUS current
            DESCRIPTION
                "Number of bytes delayed by LR."
            ::= { hwCBQoSAtmPvcLrRunInfoEntry 6 }

        
--  FR Interface PVC: policy Running statistics information
        hwCBQoSFrPvcStaticsObjects OBJECT IDENTIFIER ::= { hwCBQoSApplyPolicyStaticsObjects 3 }

        
--  FR PVC CBQ statistics
        hwCBQoSFrPvcCbqRunInfoTable OBJECT-TYPE
            SYNTAX SEQUENCE OF HwCBQoSFrPvcCbqRunInfoEntry
            MAX-ACCESS not-accessible
            STATUS current
            DESCRIPTION
                "A table of fr pvc CBQ Running statistics. When policy using queue behavior is applied on
                fr pvc fr pvc will using Class Based Queuing."
            ::= { hwCBQoSFrPvcStaticsObjects 1 }

        
        hwCBQoSFrPvcCbqRunInfoEntry OBJECT-TYPE
            SYNTAX HwCBQoSFrPvcCbqRunInfoEntry
            MAX-ACCESS not-accessible
            STATUS current
            DESCRIPTION
                "FR PVC CBQ statistics entry."
            INDEX { hwCBQoSFrPvcApplyPolicyIfIndex, hwCBQoSFrPvcApplyPolicyDlciNum }
            ::= { hwCBQoSFrPvcCbqRunInfoTable 1 }

        
        HwCBQoSFrPvcCbqRunInfoEntry ::=
            SEQUENCE { 
                hwCBQoSFrPvcCbqQueueSize
                    Integer32,
                hwCBQoSFrPvcCbqDiscard
                    Counter64,
                hwCBQoSFrPvcCbqEfQueueSize
                    Integer32,
                hwCBQoSFrPvcCbqAfQueueSize
                    Integer32,
                hwCBQoSFrPvcCbqBeQueueSize
                    Integer32,
                hwCBQoSFrPvcCbqBeActiveQueueNum
                    Integer32,
                hwCBQoSFrPvcCbqBeMaxActiveQueueNum
                    Integer32,
                hwCBQoSFrPvcCbqBeTotalQueueNum
                    Integer32,
                hwCBQoSFrPvcCbqAfAllocatedQueueNum
                    Integer32
             }

        hwCBQoSFrPvcCbqQueueSize OBJECT-TYPE
            SYNTAX Integer32
            MAX-ACCESS read-only
            STATUS current
            DESCRIPTION
                "Queue size of CBQ"
            ::= { hwCBQoSFrPvcCbqRunInfoEntry 1 }

        
        hwCBQoSFrPvcCbqDiscard OBJECT-TYPE
            SYNTAX Counter64
            MAX-ACCESS read-only
            STATUS current
            DESCRIPTION
                "The number of discarded packets which coundn't be enqueued."
            ::= { hwCBQoSFrPvcCbqRunInfoEntry 2 }

        
        hwCBQoSFrPvcCbqEfQueueSize OBJECT-TYPE
            SYNTAX Integer32
            MAX-ACCESS read-only
            STATUS current
            DESCRIPTION
                "Queue size of EF"
            ::= { hwCBQoSFrPvcCbqRunInfoEntry 3 }

        
        hwCBQoSFrPvcCbqAfQueueSize OBJECT-TYPE
            SYNTAX Integer32
            MAX-ACCESS read-only
            STATUS current
            DESCRIPTION
                "Queue size of AF"
            ::= { hwCBQoSFrPvcCbqRunInfoEntry 4 }

        
        hwCBQoSFrPvcCbqBeQueueSize OBJECT-TYPE
            SYNTAX Integer32
            MAX-ACCESS read-only
            STATUS current
            DESCRIPTION
                "Queue size of BE"
            ::= { hwCBQoSFrPvcCbqRunInfoEntry 5 }

        
        hwCBQoSFrPvcCbqBeActiveQueueNum OBJECT-TYPE
            SYNTAX Integer32
            MAX-ACCESS read-only
            STATUS current
            DESCRIPTION
                "the number of Active Be Queue"
            ::= { hwCBQoSFrPvcCbqRunInfoEntry 6 }

        
        hwCBQoSFrPvcCbqBeMaxActiveQueueNum OBJECT-TYPE
            SYNTAX Integer32
            MAX-ACCESS read-only
            STATUS current
            DESCRIPTION
                "the max number of Active Be Queue"
            ::= { hwCBQoSFrPvcCbqRunInfoEntry 7 }

        
        hwCBQoSFrPvcCbqBeTotalQueueNum OBJECT-TYPE
            SYNTAX Integer32
            MAX-ACCESS read-only
            STATUS current
            DESCRIPTION
                "the total number of Be Queue"
            ::= { hwCBQoSFrPvcCbqRunInfoEntry 8 }

        
        hwCBQoSFrPvcCbqAfAllocatedQueueNum OBJECT-TYPE
            SYNTAX Integer32
            MAX-ACCESS read-only
            STATUS current
            DESCRIPTION
                "the Allocated number of Af Queue"
            ::= { hwCBQoSFrPvcCbqRunInfoEntry 9 }

        
--  Class match statistics
        hwCBQoSFrPvcClassMatchRunInfoTable OBJECT-TYPE
            SYNTAX SEQUENCE OF HwCBQoSFrPvcClassMatchRunInfoEntry
            MAX-ACCESS not-accessible
            STATUS current
            DESCRIPTION
                "A table of Running statistics for matching a classifier
                in a QoS policy applied on FR PVC."
            ::= { hwCBQoSFrPvcStaticsObjects 2 }

        
        hwCBQoSFrPvcClassMatchRunInfoEntry OBJECT-TYPE
            SYNTAX HwCBQoSFrPvcClassMatchRunInfoEntry
            MAX-ACCESS not-accessible
            STATUS current
            DESCRIPTION
                "Classifier matching statistics entry."
            INDEX { hwCBQoSFrPvcApplyPolicyIfIndex, hwCBQoSFrPvcApplyPolicyDlciNum, hwCBQoSFrPvcApplyPolicyDirection, hwCBQoSPolicyClassIndex }
            ::= { hwCBQoSFrPvcClassMatchRunInfoTable 1 }

        
        HwCBQoSFrPvcClassMatchRunInfoEntry ::=
            SEQUENCE { 
                hwCBQoSFrPvcClassMatchedPackets
                    Counter64,
                hwCBQoSFrPvcClassMatchedBytes
                    Counter64,
                hwCBQoSFrPvcClassAverageRate
                    Counter64
             }

        hwCBQoSFrPvcClassMatchedPackets OBJECT-TYPE
            SYNTAX Counter64
            MAX-ACCESS read-only
            STATUS current
            DESCRIPTION
                "Number of packets matching a class in a QoS policy."
            ::= { hwCBQoSFrPvcClassMatchRunInfoEntry 1 }

        
        hwCBQoSFrPvcClassMatchedBytes OBJECT-TYPE
            SYNTAX Counter64
            MAX-ACCESS read-only
            STATUS current
            DESCRIPTION
                "Number of bytes matching a class in a QoS policy."
            ::= { hwCBQoSFrPvcClassMatchRunInfoEntry 2 }

        
        hwCBQoSFrPvcClassAverageRate OBJECT-TYPE
            SYNTAX Counter64
            MAX-ACCESS read-only
            STATUS current
            DESCRIPTION
                "Average rate of the traffic matching a class in a QoS policy.
                For inbound QoS policy, it is the rate of the traffic input;
                For outbound QoS policy, it is the rate of the traffic output.
                Only software QoS support this node."
            ::= { hwCBQoSFrPvcClassMatchRunInfoEntry 3 }

        
--  CAR statistics
        hwCBQoSFrPvcCarRunInfoTable OBJECT-TYPE
            SYNTAX SEQUENCE OF HwCBQoSFrPvcCarRunInfoEntry
            MAX-ACCESS not-accessible
            STATUS current
            DESCRIPTION
                "A table of Running statistics for CAR
                in a QoS policy applied on FR PVC."
            ::= { hwCBQoSFrPvcStaticsObjects 3 }

        
        hwCBQoSFrPvcCarRunInfoEntry OBJECT-TYPE
            SYNTAX HwCBQoSFrPvcCarRunInfoEntry
            MAX-ACCESS not-accessible
            STATUS current
            DESCRIPTION
                "CAR statistics entry."
            INDEX { hwCBQoSFrPvcApplyPolicyIfIndex, hwCBQoSFrPvcApplyPolicyDlciNum, hwCBQoSFrPvcApplyPolicyDirection, hwCBQoSPolicyClassIndex }
            ::= { hwCBQoSFrPvcCarRunInfoTable 1 }

        
        HwCBQoSFrPvcCarRunInfoEntry ::=
            SEQUENCE { 
                hwCBQoSFrPvcCarConformPackets
                    Counter64,
                hwCBQoSFrPvcCarConformBytes
                    Counter64,
                hwCBQoSFrPvcCarExceedPackets
                    Counter64,
                hwCBQoSFrPvcCarExceedBytes
                    Counter64,
                hwCBQoSFrPvcCarConformPacketsRate
                    Counter64,
                hwCBQoSFrPvcCarConformBytesRate
                    Counter64,
                hwCBQoSFrPvcCarExceedPacketsRate
                    Counter64,
                hwCBQoSFrPvcCarExceedBytesRate
                    Counter64
             }

        hwCBQoSFrPvcCarConformPackets OBJECT-TYPE
            SYNTAX Counter64
            MAX-ACCESS read-only
            STATUS current
            DESCRIPTION
                "Number of packets conform CIR."
            ::= { hwCBQoSFrPvcCarRunInfoEntry 1 }

        
        hwCBQoSFrPvcCarConformBytes OBJECT-TYPE
            SYNTAX Counter64
            MAX-ACCESS read-only
            STATUS current
            DESCRIPTION
                "Number of bytes conform CIR."
            ::= { hwCBQoSFrPvcCarRunInfoEntry 2 }

        
        hwCBQoSFrPvcCarExceedPackets OBJECT-TYPE
            SYNTAX Counter64
            MAX-ACCESS read-only
            STATUS current
            DESCRIPTION
                "Number of packets exceed CIR."
            ::= { hwCBQoSFrPvcCarRunInfoEntry 3 }

        
        hwCBQoSFrPvcCarExceedBytes OBJECT-TYPE
            SYNTAX Counter64
            MAX-ACCESS read-only
            STATUS current
            DESCRIPTION
                "Number of bytes exceed CIR."
            ::= { hwCBQoSFrPvcCarRunInfoEntry 4 }

        hwCBQoSFrPvcCarConformPacketsRate OBJECT-TYPE
            SYNTAX Counter64
            MAX-ACCESS read-only
            STATUS current
            DESCRIPTION
                "Rate of packets conform CIR."
            ::= { hwCBQoSFrPvcCarRunInfoEntry 5 }

        
        hwCBQoSFrPvcCarConformBytesRate OBJECT-TYPE
            SYNTAX Counter64
            MAX-ACCESS read-only
            STATUS current
            DESCRIPTION
                "Rate of bytes conform CIR."
            ::= { hwCBQoSFrPvcCarRunInfoEntry 6 }

        
        hwCBQoSFrPvcCarExceedPacketsRate OBJECT-TYPE
            SYNTAX Counter64
            MAX-ACCESS read-only
            STATUS current
            DESCRIPTION
                "Rate of packets exceed CIR."
            ::= { hwCBQoSFrPvcCarRunInfoEntry 7 }

        
        hwCBQoSFrPvcCarExceedBytesRate OBJECT-TYPE
            SYNTAX Counter64
            MAX-ACCESS read-only
            STATUS current
            DESCRIPTION
                "Rate of bytes exceed CIR."
            ::= { hwCBQoSFrPvcCarRunInfoEntry 8 }
        
--  GTS statistics
        hwCBQoSFrPvcGtsRunInfoTable OBJECT-TYPE
            SYNTAX SEQUENCE OF HwCBQoSFrPvcGtsRunInfoEntry
            MAX-ACCESS not-accessible
            STATUS current
            DESCRIPTION
                "A table of Running statistics for GTS
                in a QoS policy applied on FR PVC."
            ::= { hwCBQoSFrPvcStaticsObjects 4 }

        
        hwCBQoSFrPvcGtsRunInfoEntry OBJECT-TYPE
            SYNTAX HwCBQoSFrPvcGtsRunInfoEntry
            MAX-ACCESS not-accessible
            STATUS current
            DESCRIPTION
                "GTS statistics entry."
            INDEX { hwCBQoSFrPvcApplyPolicyIfIndex, hwCBQoSFrPvcApplyPolicyDlciNum, hwCBQoSFrPvcApplyPolicyDirection, hwCBQoSPolicyClassIndex }
            ::= { hwCBQoSFrPvcGtsRunInfoTable 1 }

        
        HwCBQoSFrPvcGtsRunInfoEntry ::=
            SEQUENCE { 
                hwCBQoSFrPvcGtsPassedPackets
                    Counter64,
                hwCBQoSFrPvcGtsPassedBytes
                    Counter64,
                hwCBQoSFrPvcGtsDiscardedPackets
                    Counter64,
                hwCBQoSFrPvcGtsDiscardedBytes
                    Counter64,
                hwCBQoSFrPvcGtsDelayedPackets
                    Counter64,
                hwCBQoSFrPvcGtsDelayedBytes
                    Counter64,
                hwCBQoSFrPvcGtsQueueSize
                    Integer32
             }

        hwCBQoSFrPvcGtsPassedPackets OBJECT-TYPE
            SYNTAX Counter64
            MAX-ACCESS read-only
            STATUS current
            DESCRIPTION
                "Number of packets passed by GTS."
            ::= { hwCBQoSFrPvcGtsRunInfoEntry 1 }

        
        hwCBQoSFrPvcGtsPassedBytes OBJECT-TYPE
            SYNTAX Counter64
            MAX-ACCESS read-only
            STATUS current
            DESCRIPTION
                "Number of bytes passed by GTS."
            ::= { hwCBQoSFrPvcGtsRunInfoEntry 2 }

        
        hwCBQoSFrPvcGtsDiscardedPackets OBJECT-TYPE
            SYNTAX Counter64
            MAX-ACCESS read-only
            STATUS current
            DESCRIPTION
                "Number of packets discarded by GTS."
            ::= { hwCBQoSFrPvcGtsRunInfoEntry 3 }

        
        hwCBQoSFrPvcGtsDiscardedBytes OBJECT-TYPE
            SYNTAX Counter64
            MAX-ACCESS read-only
            STATUS current
            DESCRIPTION
                "Number of bytes discarded by GTS."
            ::= { hwCBQoSFrPvcGtsRunInfoEntry 4 }

        
        hwCBQoSFrPvcGtsDelayedPackets OBJECT-TYPE
            SYNTAX Counter64
            MAX-ACCESS read-only
            STATUS current
            DESCRIPTION
                "Number of packets delayed by GTS."
            ::= { hwCBQoSFrPvcGtsRunInfoEntry 5 }

        
        hwCBQoSFrPvcGtsDelayedBytes OBJECT-TYPE
            SYNTAX Counter64
            MAX-ACCESS read-only
            STATUS current
            DESCRIPTION
                "Number of bytes delayed by GTS."
            ::= { hwCBQoSFrPvcGtsRunInfoEntry 6 }

        
        hwCBQoSFrPvcGtsQueueSize OBJECT-TYPE
            SYNTAX Integer32
            MAX-ACCESS read-only
            STATUS current
            DESCRIPTION
                "Queue size of GTS queue."
            ::= { hwCBQoSFrPvcGtsRunInfoEntry 7 }

        
--  Remark statistics
        hwCBQoSFrPvcRemarkRunInfoTable OBJECT-TYPE
            SYNTAX SEQUENCE OF HwCBQoSFrPvcRemarkRunInfoEntry
            MAX-ACCESS not-accessible
            STATUS current
            DESCRIPTION
                "A table of Running statistics for remarking
                in a QoS policy applied on FR PVC."
            ::= { hwCBQoSFrPvcStaticsObjects 5 }

        
        hwCBQoSFrPvcRemarkRunInfoEntry OBJECT-TYPE
            SYNTAX HwCBQoSFrPvcRemarkRunInfoEntry
            MAX-ACCESS not-accessible
            STATUS current
            DESCRIPTION
                "Remarking statistics entry."
            INDEX { hwCBQoSFrPvcApplyPolicyIfIndex, hwCBQoSFrPvcApplyPolicyDlciNum, hwCBQoSFrPvcApplyPolicyDirection, hwCBQoSPolicyClassIndex }
            ::= { hwCBQoSFrPvcRemarkRunInfoTable 1 }

        
        HwCBQoSFrPvcRemarkRunInfoEntry ::=
            SEQUENCE { 
                hwCBQoSFrPvcRemarkedPackets
                    Counter64
             }

        hwCBQoSFrPvcRemarkedPackets OBJECT-TYPE
            SYNTAX Counter64
            MAX-ACCESS read-only
            STATUS current
            DESCRIPTION
                "Number of packets remarked."
            ::= { hwCBQoSFrPvcRemarkRunInfoEntry 1 }

        
--  Queue statistics
        hwCBQoSFrPvcQueueRunInfoTable OBJECT-TYPE
            SYNTAX SEQUENCE OF HwCBQoSFrPvcQueueRunInfoEntry
            MAX-ACCESS not-accessible
            STATUS current
            DESCRIPTION
                "A table of Running statistics for queue
                in a QoS policy applied on FR PVC."
            ::= { hwCBQoSFrPvcStaticsObjects 6 }

        
        hwCBQoSFrPvcQueueRunInfoEntry OBJECT-TYPE
            SYNTAX HwCBQoSFrPvcQueueRunInfoEntry
            MAX-ACCESS not-accessible
            STATUS current
            DESCRIPTION
                "Queue statistics entry."
            INDEX { hwCBQoSFrPvcApplyPolicyIfIndex, hwCBQoSFrPvcApplyPolicyDlciNum, hwCBQoSFrPvcApplyPolicyDirection, hwCBQoSPolicyClassIndex }
            ::= { hwCBQoSFrPvcQueueRunInfoTable 1 }

        
        HwCBQoSFrPvcQueueRunInfoEntry ::=
            SEQUENCE { 
                hwCBQoSFrPvcQueueMatchedPackets
                    Counter64,
                hwCBQoSFrPvcQueueMatchedBytes
                    Counter64,
                hwCBQoSFrPvcQueueEnqueuedPackets
                    Counter64,
                hwCBQoSFrPvcQueueEnqueuedBytes
                    Counter64,
                hwCBQoSFrPvcQueueDiscardedPackets
                    Counter64,
                hwCBQoSFrPvcQueueDiscardedBytes
                    Counter64,
                hwCBQoSFrPvcQueueMatchedPacketsRate
                    Counter64,
                hwCBQoSFrPvcQueueMatchedBytesRate
                    Counter64,
                hwCBQoSFrPvcQueueEnqueuedPacketsRate
                    Counter64,
                hwCBQoSFrPvcQueueEnqueuedBytesRate
                    Counter64,
                hwCBQoSFrPvcQueueDiscardedPacketsRate
                    Counter64,
                hwCBQoSFrPvcQueueDiscardedBytesRate
                    Counter64
             }

        hwCBQoSFrPvcQueueMatchedPackets OBJECT-TYPE
            SYNTAX Counter64
            MAX-ACCESS read-only
            STATUS current
            DESCRIPTION
                "Number of packets matched to enqueue."
            ::= { hwCBQoSFrPvcQueueRunInfoEntry 1 }

        
        hwCBQoSFrPvcQueueMatchedBytes OBJECT-TYPE
            SYNTAX Counter64
            MAX-ACCESS read-only
            STATUS current
            DESCRIPTION
                "Number of bytes matched to enqueue."
            ::= { hwCBQoSFrPvcQueueRunInfoEntry 2 }

        
        hwCBQoSFrPvcQueueEnqueuedPackets OBJECT-TYPE
            SYNTAX Counter64
            MAX-ACCESS read-only
            STATUS current
            DESCRIPTION
                "Number of packets enqueued."
            ::= { hwCBQoSFrPvcQueueRunInfoEntry 3 }

        
        hwCBQoSFrPvcQueueEnqueuedBytes OBJECT-TYPE
            SYNTAX Counter64
            MAX-ACCESS read-only
            STATUS current
            DESCRIPTION
                "Number of bytes enqueued."
            ::= { hwCBQoSFrPvcQueueRunInfoEntry 4 }

        
        hwCBQoSFrPvcQueueDiscardedPackets OBJECT-TYPE
            SYNTAX Counter64
            MAX-ACCESS read-only
            STATUS current
            DESCRIPTION
                "Number of packets discarded when enqueued by discard method."
            ::= { hwCBQoSFrPvcQueueRunInfoEntry 5 }

        
        hwCBQoSFrPvcQueueDiscardedBytes OBJECT-TYPE
            SYNTAX Counter64
            MAX-ACCESS read-only
            STATUS current
            DESCRIPTION
                "Number of bytes discarded when enqueued by discard method."
            ::= { hwCBQoSFrPvcQueueRunInfoEntry 6 }

        hwCBQoSFrPvcQueueMatchedPacketsRate OBJECT-TYPE
            SYNTAX Counter64
            MAX-ACCESS read-only
            STATUS current
            DESCRIPTION
                "Rate of packets matched to enqueue."
            ::= { hwCBQoSFrPvcQueueRunInfoEntry 7 }

        
        hwCBQoSFrPvcQueueMatchedBytesRate OBJECT-TYPE
            SYNTAX Counter64
            MAX-ACCESS read-only
            STATUS current
            DESCRIPTION
                "Rate of bytes matched to enqueue."
            ::= { hwCBQoSFrPvcQueueRunInfoEntry 8 }

        
        hwCBQoSFrPvcQueueEnqueuedPacketsRate OBJECT-TYPE
            SYNTAX Counter64
            MAX-ACCESS read-only
            STATUS current
            DESCRIPTION
                "Rate of packets enqueued."
            ::= { hwCBQoSFrPvcQueueRunInfoEntry 9 }

        
        hwCBQoSFrPvcQueueEnqueuedBytesRate OBJECT-TYPE
            SYNTAX Counter64
            MAX-ACCESS read-only
            STATUS current
            DESCRIPTION
                "Rate of bytes enqueued."
            ::= { hwCBQoSFrPvcQueueRunInfoEntry 10 }

        
        hwCBQoSFrPvcQueueDiscardedPacketsRate OBJECT-TYPE
            SYNTAX Counter64
            MAX-ACCESS read-only
            STATUS current
            DESCRIPTION
                "Rate of packets discarded when enqueued by discard method."
            ::= { hwCBQoSFrPvcQueueRunInfoEntry 11 }

        
        hwCBQoSFrPvcQueueDiscardedBytesRate OBJECT-TYPE
            SYNTAX Counter64
            MAX-ACCESS read-only
            STATUS current
            DESCRIPTION
                "Rate of bytes discarded when enqueued by discard method."
            ::= { hwCBQoSFrPvcQueueRunInfoEntry 12 }
        
--  WRED statistics
        hwCBQoSFrPvcWredRunInfoTable OBJECT-TYPE
            SYNTAX SEQUENCE OF HwCBQoSFrPvcWredRunInfoEntry
            MAX-ACCESS not-accessible
            STATUS current
            DESCRIPTION
                "A table of Running statistics for WRED
                in a QoS policy applied on FR PVC."
            ::= { hwCBQoSFrPvcStaticsObjects 7 }

        
        hwCBQoSFrPvcWredRunInfoEntry OBJECT-TYPE
            SYNTAX HwCBQoSFrPvcWredRunInfoEntry
            MAX-ACCESS not-accessible
            STATUS current
            DESCRIPTION
                "WRED statistics entry."
            INDEX { hwCBQoSFrPvcApplyPolicyIfIndex, hwCBQoSFrPvcApplyPolicyDlciNum, hwCBQoSFrPvcApplyPolicyDirection, hwCBQoSPolicyClassIndex, hwCBQoSWredClassValue
                 }
            ::= { hwCBQoSFrPvcWredRunInfoTable 1 }

        
        HwCBQoSFrPvcWredRunInfoEntry ::=
            SEQUENCE { 
                hwCBQoSFrPvcWredRandomDiscardedPackets
                    Counter64,
                hwCBQoSFrPvcWredTailDiscardedPackets
                    Counter64
             }

        hwCBQoSFrPvcWredRandomDiscardedPackets OBJECT-TYPE
            SYNTAX Counter64
            MAX-ACCESS read-only
            STATUS current
            DESCRIPTION
                "Number of packets randomly discarded by WRED."
            ::= { hwCBQoSFrPvcWredRunInfoEntry 1 }

        
        hwCBQoSFrPvcWredTailDiscardedPackets OBJECT-TYPE
            SYNTAX Counter64
            MAX-ACCESS read-only
            STATUS current
            DESCRIPTION
                "Number of packets tail-discarded by WRED."
            ::= { hwCBQoSFrPvcWredRunInfoEntry 2 }

        
--  LR statistics
        hwCBQoSFrPvcLrRunInfoTable OBJECT-TYPE
            SYNTAX SEQUENCE OF HwCBQoSFrPvcLrRunInfoEntry
            MAX-ACCESS not-accessible
            STATUS current
            DESCRIPTION
                "A table of Running statistics for LR
                in a QoS policy applied on FR PVC."
            ::= { hwCBQoSFrPvcStaticsObjects 8 }

        
        hwCBQoSFrPvcLrRunInfoEntry OBJECT-TYPE
            SYNTAX HwCBQoSFrPvcLrRunInfoEntry
            MAX-ACCESS not-accessible
            STATUS current
            DESCRIPTION
                "LR statistics entry."
            INDEX { hwCBQoSFrPvcApplyPolicyIfIndex, hwCBQoSFrPvcApplyPolicyDlciNum, hwCBQoSFrPvcApplyPolicyDirection, hwCBQoSPolicyClassIndex }
            ::= { hwCBQoSFrPvcLrRunInfoTable 1 }

        
        HwCBQoSFrPvcLrRunInfoEntry ::=
            SEQUENCE { 
                hwCBQoSFrPvcLrPassedPackets
                    Counter64,
                hwCBQoSFrPvcLrPassedBytes
                    Counter64,
                hwCBQoSFrPvcLrDiscardedPackets
                    Counter64,
                hwCBQoSFrPvcLrDiscardedBytes
                    Counter64,
                hwCBQoSFrPvcLrDelayedPackets
                    Counter64,
                hwCBQoSFrPvcLrDelayedBytes
                    Counter64
             }

        hwCBQoSFrPvcLrPassedPackets OBJECT-TYPE
            SYNTAX Counter64
            MAX-ACCESS read-only
            STATUS current
            DESCRIPTION
                "Number of packets passed by LR."
            ::= { hwCBQoSFrPvcLrRunInfoEntry 1 }

        
        hwCBQoSFrPvcLrPassedBytes OBJECT-TYPE
            SYNTAX Counter64
            MAX-ACCESS read-only
            STATUS current
            DESCRIPTION
                "Number of bytes passed by LR."
            ::= { hwCBQoSFrPvcLrRunInfoEntry 2 }

        
        hwCBQoSFrPvcLrDiscardedPackets OBJECT-TYPE
            SYNTAX Counter64
            MAX-ACCESS read-only
            STATUS current
            DESCRIPTION
                "Number of packets discarded by LR."
            ::= { hwCBQoSFrPvcLrRunInfoEntry 3 }

        
        hwCBQoSFrPvcLrDiscardedBytes OBJECT-TYPE
            SYNTAX Counter64
            MAX-ACCESS read-only
            STATUS current
            DESCRIPTION
                "Number of bytes discarded by LR."
            ::= { hwCBQoSFrPvcLrRunInfoEntry 4 }

        
        hwCBQoSFrPvcLrDelayedPackets OBJECT-TYPE
            SYNTAX Counter64
            MAX-ACCESS read-only
            STATUS current
            DESCRIPTION
                "Number of packets delayed by LR."
            ::= { hwCBQoSFrPvcLrRunInfoEntry 5 }

        
        hwCBQoSFrPvcLrDelayedBytes OBJECT-TYPE
            SYNTAX Counter64
            MAX-ACCESS read-only
            STATUS current
            DESCRIPTION
                "Number of bytes delayed by LR."
            ::= { hwCBQoSFrPvcLrRunInfoEntry 6 }

        
--  Ethernet Interface VLAN: policy Running statistics information
        hwCBQoSIfVlanStaticsObjects OBJECT IDENTIFIER ::= { hwCBQoSApplyPolicyStaticsObjects 4 }

        
--  Class match statistics
        hwCBQoSIfVlanClassMatchRunInfoTable OBJECT-TYPE
            SYNTAX SEQUENCE OF HwCBQoSIfVlanClassMatchRunInfoEntry
            MAX-ACCESS not-accessible
            STATUS current
            DESCRIPTION
                "A table of Running statistics for matching a classifier
                in a QoS policy applied on ethernet vlan."
            ::= { hwCBQoSIfVlanStaticsObjects 1 }

        
        hwCBQoSIfVlanClassMatchRunInfoEntry OBJECT-TYPE
            SYNTAX HwCBQoSIfVlanClassMatchRunInfoEntry
            MAX-ACCESS not-accessible
            STATUS current
            DESCRIPTION
                "Classifier matching statistics entry."
            INDEX { hwCBQoSIfVlanApplyPolicyIfIndex, hwCBQoSIfVlanApplyPolicyVlanid1, hwCBQoSIfVlanApplyPolicyDirection, hwCBQoSPolicyClassIndex }
            ::= { hwCBQoSIfVlanClassMatchRunInfoTable 1 }

        
        HwCBQoSIfVlanClassMatchRunInfoEntry ::=
            SEQUENCE { 
                hwCBQoSIfVlanClassMatchedPackets
                    Counter64,
                hwCBQoSIfVlanClassMatchedBytes
                    Counter64
             }

        hwCBQoSIfVlanClassMatchedPackets OBJECT-TYPE
            SYNTAX Counter64
            MAX-ACCESS read-only
            STATUS current
            DESCRIPTION
                "Number of packets matching a class in a QoS policy."
            ::= { hwCBQoSIfVlanClassMatchRunInfoEntry 1 }

        
        hwCBQoSIfVlanClassMatchedBytes OBJECT-TYPE
            SYNTAX Counter64
            MAX-ACCESS read-only
            STATUS current
            DESCRIPTION
                "Number of Bytes matching a class in a QoS policy."
            ::= { hwCBQoSIfVlanClassMatchRunInfoEntry 2 }

        
--  Ethernet Interface VSI: policy Running statistics information
        hwCBQoSVsiStaticsObjects OBJECT IDENTIFIER ::= { hwCBQoSApplyPolicyStaticsObjects 5 }

        
--  Class match statistics
        hwCBQoSVsiClassMatchRunInfoTable OBJECT-TYPE
            SYNTAX SEQUENCE OF HwCBQoSVsiClassMatchRunInfoEntry
            MAX-ACCESS not-accessible
            STATUS current
            DESCRIPTION
                "A table of Running statistics for matching a classifier
                in a QoS policy applied on VSI."
            ::= { hwCBQoSVsiStaticsObjects 1 }

        
        hwCBQoSVsiClassMatchRunInfoEntry OBJECT-TYPE
            SYNTAX HwCBQoSVsiClassMatchRunInfoEntry
            MAX-ACCESS not-accessible
            STATUS current
            DESCRIPTION
                "Classifier matching statistics entry."
            INDEX { hwCBQoSVsiApplyPolicyVsiIndex, hwCBQoSVsiApplyPolicyDirection, hwCBQoSPolicyClassIndex }
            ::= { hwCBQoSVsiClassMatchRunInfoTable 1 }

        
        HwCBQoSVsiClassMatchRunInfoEntry ::=
            SEQUENCE { 
                hwCBQoSVsiClassMatchedPackets
                    Counter64,
                hwCBQoSVsiClassMatchedBytes
                    Counter64
             }

        hwCBQoSVsiClassMatchedPackets OBJECT-TYPE
            SYNTAX Counter64
            MAX-ACCESS read-only
            STATUS current
            DESCRIPTION
                "Number of packets matching a class in a QoS policy."
            ::= { hwCBQoSVsiClassMatchRunInfoEntry 1 }

        
        hwCBQoSVsiClassMatchedBytes OBJECT-TYPE
            SYNTAX Counter64
            MAX-ACCESS read-only
            STATUS current
            DESCRIPTION
                "Number of Bytes matching a class in a QoS policy."
            ::= { hwCBQoSVsiClassMatchRunInfoEntry 2 }

        
--  Policy car statistics
        hwCBQoSPolicyStatisticsObjects OBJECT IDENTIFIER ::= { hwCBQoSApplyPolicyStaticsObjects 6 }

        
        hwCBQoSCarStatisticsTable OBJECT-TYPE
            SYNTAX SEQUENCE OF HwCBQoSCarStatisticsEntry
            MAX-ACCESS not-accessible
            STATUS current
            DESCRIPTION
                "This table describes the traffic policing and statistics based on the traffic classification, including the statistics of the traffic within CIR, between CIR and PIR, and beyond PIR."
            ::= { hwCBQoSPolicyStatisticsObjects 1 }

        
        hwCBQoSCarStatisticsEntry OBJECT-TYPE
            SYNTAX HwCBQoSCarStatisticsEntry
            MAX-ACCESS not-accessible
            STATUS current
            DESCRIPTION
                "A table of CAR statistics for class-based traffic classification applied
                in traffic monitoring, including the statistics of  packets that have the
                rate within CIR, of CIR, of PIR or exceeds PIR."
            INDEX { hwCBQoSIfApplyPolicyIfIndex, hwCBQoSIfApplyPolicyDirection, hwCBQoSIfVlanApplyPolicyVlanid1, hwCBQoSIfVlanApplyPolicyVlanid2, hwCBQoSPolicyClassIndex }
            ::= { hwCBQoSCarStatisticsTable 1 }

        
        HwCBQoSCarStatisticsEntry ::=
            SEQUENCE { 
                hwCBQoSCarConformedPackets
                    Counter64,
                hwCBQoSCarConformedBytes
                    Counter64,
                hwCBQoSCarConformedPacketRate
                    Counter64,
                hwCBQoSCarConformedByteRate
                    Counter64,
                hwCBQoSCarExceededPackets
                    Counter64,
                hwCBQoSCarExceededBytes
                    Counter64,
                hwCBQoSCarExceededPacketRate
                    Counter64,
                hwCBQoSCarExceededByteRate
                    Counter64,
                hwCBQoSCarOverflowPackets
                    Counter64,
                hwCBQoSCarOverflowBytes
                    Counter64,
                hwCBQoSCarOverflowPacketRate
                    Counter64,
                hwCBQoSCarOverflowByteRate
                    Counter64,
                hwCBQoSCarPassedPackets
                    Counter64,
                hwCBQoSCarPassedBytes
                    Counter64,
                hwCBQoSCarDroppedPackets
                    Counter64,
                hwCBQoSCarDroppedBytes
                    Counter64
             }

        hwCBQoSCarConformedPackets OBJECT-TYPE
            SYNTAX Counter64
            MAX-ACCESS read-only
            STATUS current
            DESCRIPTION
                "This object indicates the number of packets within the range of CIR."
            ::= { hwCBQoSCarStatisticsEntry 11 }

        
        hwCBQoSCarConformedBytes OBJECT-TYPE
            SYNTAX Counter64
            MAX-ACCESS read-only
            STATUS current
            DESCRIPTION
                "This object indicates the number of bytes within the range of CIR."
            ::= { hwCBQoSCarStatisticsEntry 12 }

        
        hwCBQoSCarConformedPacketRate OBJECT-TYPE
            SYNTAX Counter64
            MAX-ACCESS read-only
            STATUS current
            DESCRIPTION
                "This object indicates the packet rate within the range of CIR, in pps."
            ::= { hwCBQoSCarStatisticsEntry 13 }

        
        hwCBQoSCarConformedByteRate OBJECT-TYPE
            SYNTAX Counter64
            MAX-ACCESS read-only
            STATUS current
            DESCRIPTION
                "This object indicates the bytes rate within the range of CIR, in Bps."
            ::= { hwCBQoSCarStatisticsEntry 14 }

        
        hwCBQoSCarExceededPackets OBJECT-TYPE
            SYNTAX Counter64
            MAX-ACCESS read-only
            STATUS current
            DESCRIPTION
                "This object indicates the number of packets between PIR and CIR."
            ::= { hwCBQoSCarStatisticsEntry 15 }

        
        hwCBQoSCarExceededBytes OBJECT-TYPE
            SYNTAX Counter64
            MAX-ACCESS read-only
            STATUS current
            DESCRIPTION
                "This object indicates the number of bytes between PIR and CIR."
            ::= { hwCBQoSCarStatisticsEntry 16 }

        
        hwCBQoSCarExceededPacketRate OBJECT-TYPE
            SYNTAX Counter64
            MAX-ACCESS read-only
            STATUS current
            DESCRIPTION
                "This object indicates the packet rate between PIR and CIR, in pps."
            ::= { hwCBQoSCarStatisticsEntry 17 }

        
        hwCBQoSCarExceededByteRate OBJECT-TYPE
            SYNTAX Counter64
            MAX-ACCESS read-only
            STATUS current
            DESCRIPTION
                "This object indicates the byte rate between PIR and CIR, in Bps."
            ::= { hwCBQoSCarStatisticsEntry 18 }

        
        hwCBQoSCarOverflowPackets OBJECT-TYPE
            SYNTAX Counter64
            MAX-ACCESS read-only
            STATUS current
            DESCRIPTION
                "This object indicates the rate of packets that exceeds the PIR."
            ::= { hwCBQoSCarStatisticsEntry 19 }

        
        hwCBQoSCarOverflowBytes OBJECT-TYPE
            SYNTAX Counter64
            MAX-ACCESS read-only
            STATUS current
            DESCRIPTION
                "This object indicates the number of bytes when PIR is exceeded."
            ::= { hwCBQoSCarStatisticsEntry 20 }

        
        hwCBQoSCarOverflowPacketRate OBJECT-TYPE
            SYNTAX Counter64
            MAX-ACCESS read-only
            STATUS current
            DESCRIPTION
                "This object indicates the rate of packets that exceeds the PIR."
            ::= { hwCBQoSCarStatisticsEntry 21 }

        
        hwCBQoSCarOverflowByteRate OBJECT-TYPE
            SYNTAX Counter64
            MAX-ACCESS read-only
            STATUS current
            DESCRIPTION
                "This object indicates the rate of bytes that exceeds the PIR, in Bps."
            ::= { hwCBQoSCarStatisticsEntry 22 }

        
        hwCBQoSCarPassedPackets OBJECT-TYPE
            SYNTAX Counter64
            MAX-ACCESS read-only
            STATUS current
            DESCRIPTION
                "This object indicates the number of packets passed after the Committed Access Rate (CAR) is set."
            ::= { hwCBQoSCarStatisticsEntry 23 }

        
        hwCBQoSCarPassedBytes OBJECT-TYPE
            SYNTAX Counter64
            MAX-ACCESS read-only
            STATUS current
            DESCRIPTION
                "This object indicates the number of the bytes passed after CAR is set."
            ::= { hwCBQoSCarStatisticsEntry 24 }

        
        hwCBQoSCarDroppedPackets OBJECT-TYPE
            SYNTAX Counter64
            MAX-ACCESS read-only
            STATUS current
            DESCRIPTION
                "This object indicates the number of discarded packets after CAR is set."
            ::= { hwCBQoSCarStatisticsEntry 25 }

        
        hwCBQoSCarDroppedBytes OBJECT-TYPE
            SYNTAX Counter64
            MAX-ACCESS read-only
            STATUS current
            DESCRIPTION
                "This object indicates the number of discarded bytes after CAR is set."
            ::= { hwCBQoSCarStatisticsEntry 26 }

        
--  policy statics
        hwCBQoSPolicyStatisticsTable OBJECT-TYPE
            SYNTAX SEQUENCE OF HwCBQoSPolicyStatisticsEntry
            MAX-ACCESS not-accessible
            STATUS current
            DESCRIPTION
                "This table describes the policy-based statistics.
"
            ::= { hwCBQoSPolicyStatisticsObjects 2 }

        
        hwCBQoSPolicyStatisticsEntry OBJECT-TYPE
            SYNTAX HwCBQoSPolicyStatisticsEntry
            MAX-ACCESS not-accessible
            STATUS current
            DESCRIPTION
                "Statistics information of the policy."
            INDEX { hwCBQoSIfApplyPolicyIfIndex, hwCBQoSIfApplyPolicyDirection, hwCBQoSIfVlanApplyPolicyVlanid1, hwCBQoSIfVlanApplyPolicyVlanid2 }
            ::= { hwCBQoSPolicyStatisticsTable 1 }

        
        HwCBQoSPolicyStatisticsEntry ::=
            SEQUENCE { 
                hwCBQoSPolicyMatchedPackets
                    Counter64,
                hwCBQoSPolicyMatchedBytes
                    Counter64,
                hwCBQoSPolicyUnmatchedPackets
                    Counter64,
                hwCBQoSPolicyUnmatchedBytes
                    Counter64,
                hwCBQoSPolicyMatchedPassPackets
                    Counter64,
                hwCBQoSPolicyMatchedPassBytes
                    Counter64,
                hwCBQoSPolicyMatchedDropPackets
                    Counter64,
                hwCBQoSPolicyMatchedDropBytes
                    Counter64,
                hwCBQoSPolicyResetFlag
                    EnabledStatus,
                hwCBQoSPolicyMatchedPacketsRate
                    Counter64,
                hwCBQoSPolicyMatchedBytesRate
                    Counter64,
                hwCBQoSPolicyMatchedPassPacketsRate
                    Counter64,
                hwCBQoSPolicyMatchedPassBytesRate
                    Counter64,
                hwCBQoSPolicyMatchedDropPacketsRate
                    Counter64,
                hwCBQoSPolicyMatchedDropBytesRate
                    Counter64               
             }

        hwCBQoSPolicyMatchedPackets OBJECT-TYPE
            SYNTAX Counter64
            MAX-ACCESS read-only
            STATUS current
            DESCRIPTION
                "This object indicates the number of packets matching the traffic classification policy."
            ::= { hwCBQoSPolicyStatisticsEntry 11 }

        
        hwCBQoSPolicyMatchedBytes OBJECT-TYPE
            SYNTAX Counter64
            MAX-ACCESS read-only
            STATUS current
            DESCRIPTION
                "This object indicates the number of bytes matching the traffic classification policy."
            ::= { hwCBQoSPolicyStatisticsEntry 12 }

        
        hwCBQoSPolicyUnmatchedPackets OBJECT-TYPE
            SYNTAX Counter64
            MAX-ACCESS read-only
            STATUS current
            DESCRIPTION
                "This object indicates the number of packets mismatching the traffic classification policy."
            ::= { hwCBQoSPolicyStatisticsEntry 13 }

        
        hwCBQoSPolicyUnmatchedBytes OBJECT-TYPE
            SYNTAX Counter64
            MAX-ACCESS read-only
            STATUS current
            DESCRIPTION
                "This object indicates the number of bytes mismatching the traffic classification policy."
            ::= { hwCBQoSPolicyStatisticsEntry 14 } 

        hwCBQoSPolicyMatchedPassPackets OBJECT-TYPE
            SYNTAX Counter64
            MAX-ACCESS read-only
            STATUS current
            DESCRIPTION
                "Number of packets that match the traffic classification policy and pass through"
            ::= { hwCBQoSPolicyStatisticsEntry 15 }
            
        hwCBQoSPolicyMatchedPassBytes OBJECT-TYPE
            SYNTAX Counter64
            MAX-ACCESS read-only
            STATUS current
            DESCRIPTION
                "Number of bytes that match the traffic classification policy and pass through"
            ::= { hwCBQoSPolicyStatisticsEntry 16 }
            
        hwCBQoSPolicyMatchedDropPackets OBJECT-TYPE
            SYNTAX Counter64
            MAX-ACCESS read-only
            STATUS current
            DESCRIPTION
                "Number of packets that match the traffic classification policy and are discarded"
            ::= { hwCBQoSPolicyStatisticsEntry 17 }
            
        hwCBQoSPolicyMatchedDropBytes OBJECT-TYPE
            SYNTAX Counter64
            MAX-ACCESS read-only
            STATUS current
            DESCRIPTION
                "Number of bytes that match the traffic classification policy and are discarded"
            ::= { hwCBQoSPolicyStatisticsEntry 18 }
            
        hwCBQoSPolicyResetFlag OBJECT-TYPE
            SYNTAX EnabledStatus
            MAX-ACCESS read-write
            STATUS current
            DESCRIPTION
                "Reset flag enable(1),disable(2)."
            ::= { hwCBQoSPolicyStatisticsEntry 19 }

        hwCBQoSPolicyMatchedPacketsRate OBJECT-TYPE
            SYNTAX Counter64
            MAX-ACCESS read-only
            STATUS current
            DESCRIPTION
                "This object indicates the rate of packets matching the traffic classification policy."
            ::= { hwCBQoSPolicyStatisticsEntry 20 }

        
        hwCBQoSPolicyMatchedBytesRate OBJECT-TYPE
            SYNTAX Counter64
            MAX-ACCESS read-only
            STATUS current
            DESCRIPTION
                "This object indicates the rate of bytes matching the traffic classification policy."
            ::= { hwCBQoSPolicyStatisticsEntry 21 }

        hwCBQoSPolicyMatchedPassPacketsRate OBJECT-TYPE
            SYNTAX Counter64
            MAX-ACCESS read-only
            STATUS current
            DESCRIPTION
                "Rate of packets that match the traffic classification policy and pass through"
            ::= { hwCBQoSPolicyStatisticsEntry 22 }
            
        hwCBQoSPolicyMatchedPassBytesRate OBJECT-TYPE
            SYNTAX Counter64
            MAX-ACCESS read-only
            STATUS current
            DESCRIPTION
                "Rate of bytes that match the traffic classification policy and pass through"
            ::= { hwCBQoSPolicyStatisticsEntry 23 }
            
        hwCBQoSPolicyMatchedDropPacketsRate OBJECT-TYPE
            SYNTAX Counter64
            MAX-ACCESS read-only
            STATUS current
            DESCRIPTION
                "Rate of packets that match the traffic classification policy and are discarded"
            ::= { hwCBQoSPolicyStatisticsEntry 24 }
            
        hwCBQoSPolicyMatchedDropBytesRate OBJECT-TYPE
            SYNTAX Counter64
            MAX-ACCESS read-only
            STATUS current
            DESCRIPTION
                "Rate of bytes that match the traffic classification policy and are discarded"
            ::= { hwCBQoSPolicyStatisticsEntry 25 }

--  classifier statistics
        hwCBQoSClassifierStatisticsTable OBJECT-TYPE
            SYNTAX SEQUENCE OF HwCBQoSClassifierStatisticsEntry
            MAX-ACCESS not-accessible
            STATUS current
            DESCRIPTION
                "This table lists statistics on traffic classifiers."
            ::= { hwCBQoSPolicyStatisticsObjects 3 }
            
        hwCBQoSClassifierStatisticsEntry OBJECT-TYPE
            SYNTAX HwCBQoSClassifierStatisticsEntry
            MAX-ACCESS not-accessible
            STATUS current
            DESCRIPTION
                "Statistics information of the class."
            INDEX { hwCBQoSIfApplyPolicyIfIndex, hwCBQoSIfApplyPolicyDirection, hwCBQoSIfVlanApplyPolicyVlanid1, hwCBQoSIfVlanApplyPolicyVlanid2, hwCBQoSPolicyClassifierIndex}
            ::= { hwCBQoSClassifierStatisticsTable 1 }

        
        HwCBQoSClassifierStatisticsEntry ::=
            SEQUENCE {
                hwCBQoSPolicyClassifierIndex
                    Integer32,
                hwCBQoSClassifierMatchedPackets
                    Counter64,
                hwCBQoSClassifierMatchedBytes
                    Counter64,
                hwCBQoSClassifierMatchedPassPackets
                    Counter64,
                hwCBQoSClassifierMatchedPassBytes
                    Counter64,
                hwCBQoSClassifierMatchedDropPackets
                    Counter64,
                hwCBQoSClassifierMatchedDropBytes
                    Counter64
             }
                         
        hwCBQoSPolicyClassifierIndex OBJECT-TYPE
            SYNTAX Integer32
            MAX-ACCESS read-only
            STATUS current
            DESCRIPTION
                "Indicates the index of a traffic class."
            ::= { hwCBQoSClassifierStatisticsEntry 4 }
                  
        hwCBQoSClassifierMatchedPackets OBJECT-TYPE
            SYNTAX Counter64
            MAX-ACCESS read-only
            STATUS current
            DESCRIPTION
                "Indicates the number of packets that match the class."
            ::= { hwCBQoSClassifierStatisticsEntry 5 }

        
        hwCBQoSClassifierMatchedBytes OBJECT-TYPE
            SYNTAX Counter64
            MAX-ACCESS read-only
            STATUS current
            DESCRIPTION
                "Indicates the number of matched bytes."
            ::= { hwCBQoSClassifierStatisticsEntry 6 }     
        
        hwCBQoSClassifierMatchedPassPackets OBJECT-TYPE
            SYNTAX Counter64
            MAX-ACCESS read-only
            STATUS current
            DESCRIPTION
                "Indicates the matched and passed traffic in packets."
            ::= { hwCBQoSClassifierStatisticsEntry 7 }
            
        hwCBQoSClassifierMatchedPassBytes OBJECT-TYPE
            SYNTAX Counter64
            MAX-ACCESS read-only
            STATUS current
            DESCRIPTION
                "Indicates the matched and passed traffic in bytes."
            ::= { hwCBQoSClassifierStatisticsEntry 8 }
            
        hwCBQoSClassifierMatchedDropPackets OBJECT-TYPE
            SYNTAX Counter64
            MAX-ACCESS read-only
            STATUS current
            DESCRIPTION
                "Indicates the matched and discarded traffic in packets."
            ::= { hwCBQoSClassifierStatisticsEntry 9 }
            
        hwCBQoSClassifierMatchedDropBytes OBJECT-TYPE
            SYNTAX Counter64
            MAX-ACCESS read-only
            STATUS current
            DESCRIPTION
                "Indicates the matched and discarded traffic in bytes."
            ::= { hwCBQoSClassifierStatisticsEntry 10 }            
            


        
        
--  class based policy stat     
        hwCBQoSPolicyStatisticsClassifierTable OBJECT-TYPE
            SYNTAX SEQUENCE OF HwCBQoSPolicyStatisticsClassifierEntry
            MAX-ACCESS not-accessible
            STATUS current
            DESCRIPTION
                "This table records classifier statistics."
            ::= { hwCBQoSPolicyStatisticsObjects 4 }
        
        hwCBQoSPolicyStatisticsClassifierEntry OBJECT-TYPE
            SYNTAX HwCBQoSPolicyStatisticsClassifierEntry
            MAX-ACCESS not-accessible
            STATUS current
            DESCRIPTION
                "Class based policy statistics entry."
            INDEX { hwCBQoSIfApplyPolicyIfIndex , hwCBQoSIfVlanApplyPolicyVlanid1, hwCBQoSIfApplyPolicyDirection, hwCBQoSPolicyStatClassifierName
                 }
            ::= { hwCBQoSPolicyStatisticsClassifierTable 1 }
        
        HwCBQoSPolicyStatisticsClassifierEntry ::=
            SEQUENCE { 
                hwCBQoSPolicyStatClassifierName
                    OCTET STRING,
                hwCBQoSPolicyStatClassifierMatchedPackets
                    Counter64,
                hwCBQoSPolicyStatClassifierMatchedBytes
                    Counter64,
                hwCBQoSPolicyStatClassifierUnmatchedPackets
                    Counter64,
                hwCBQoSPolicyStatClassifierUnmatchedBytes
                    Counter64,
                hwCBQoSPolicyStatClassifierMatchedPassPackets
                    Counter64,
                hwCBQoSPolicyStatClassifierMatchedPassBytes
                    Counter64,
                hwCBQoSPolicyStatClassifierMatchedDropPackets
                    Counter64,
                hwCBQoSPolicyStatClassifierMatchedDropBytes
                    Counter64,
                hwCBQoSPolicyStatClassifierMatchedPacketsRate
                    Counter64,
                hwCBQoSPolicyStatClassifierMatchedBytesRate
                    Counter64,
                hwCBQoSPolicyStatClassifierMatchedPassPacketsRate
                    Counter64,
                hwCBQoSPolicyStatClassifierMatchedPassBytesRate
                    Counter64,
                hwCBQoSPolicyStatClassifierMatchedDropPacketsRate
                    Counter64,
                hwCBQoSPolicyStatClassifierMatchedDropBytesRate
                    Counter64
                    }

        hwCBQoSPolicyStatClassifierName OBJECT-TYPE
            SYNTAX OCTET STRING (SIZE (1..64))
            MAX-ACCESS read-only
            STATUS current
            DESCRIPTION
                "Name of classifier."
            ::= { hwCBQoSPolicyStatisticsClassifierEntry 1 }
        
        hwCBQoSPolicyStatClassifierMatchedPackets OBJECT-TYPE
            SYNTAX Counter64
            MAX-ACCESS read-only
            STATUS current
            DESCRIPTION
                "Number of matched packets."
            ::= { hwCBQoSPolicyStatisticsClassifierEntry 2 }
        
        hwCBQoSPolicyStatClassifierMatchedBytes OBJECT-TYPE
            SYNTAX Counter64
            MAX-ACCESS read-only
            STATUS current
            DESCRIPTION
                "Number of matched bytes."
            ::= { hwCBQoSPolicyStatisticsClassifierEntry 3 }
        

        hwCBQoSPolicyStatClassifierUnmatchedPackets OBJECT-TYPE
            SYNTAX Counter64
            MAX-ACCESS read-only
            STATUS current
            DESCRIPTION
                "Number of unmatched packets."
            ::= { hwCBQoSPolicyStatisticsClassifierEntry 4 }
        

        hwCBQoSPolicyStatClassifierUnmatchedBytes OBJECT-TYPE
            SYNTAX Counter64
            MAX-ACCESS read-only
            STATUS current
            DESCRIPTION
                "Number of unmatched bytes."
            ::= { hwCBQoSPolicyStatisticsClassifierEntry 5 }
        

        hwCBQoSPolicyStatClassifierMatchedPassPackets OBJECT-TYPE
            SYNTAX Counter64
            MAX-ACCESS read-only
            STATUS current
            DESCRIPTION
                "Number of packets that match the traffic classifier and pass through"
            ::= { hwCBQoSPolicyStatisticsClassifierEntry 6 }
            

        hwCBQoSPolicyStatClassifierMatchedPassBytes OBJECT-TYPE
            SYNTAX Counter64
            MAX-ACCESS read-only
            STATUS current
            DESCRIPTION
                "Number of bytes that match the traffic classifier and pass through"
            ::= { hwCBQoSPolicyStatisticsClassifierEntry 7 }
            

        hwCBQoSPolicyStatClassifierMatchedDropPackets OBJECT-TYPE
            SYNTAX Counter64
            MAX-ACCESS read-only
            STATUS current
            DESCRIPTION
                "Number of packets that match the traffic classification policy and are discarded"
            ::= { hwCBQoSPolicyStatisticsClassifierEntry 8 }
            

        hwCBQoSPolicyStatClassifierMatchedDropBytes OBJECT-TYPE
            SYNTAX Counter64
            MAX-ACCESS read-only
            STATUS current
            DESCRIPTION
                "Number of bytes that match the traffic classification policy and are discarded"
            ::= { hwCBQoSPolicyStatisticsClassifierEntry 9 }

        hwCBQoSPolicyStatClassifierMatchedPacketsRate OBJECT-TYPE
            SYNTAX Counter64
            MAX-ACCESS read-only
            STATUS current
            DESCRIPTION
                "Rate of matched packets."
            ::= { hwCBQoSPolicyStatisticsClassifierEntry 10 }
        
        hwCBQoSPolicyStatClassifierMatchedBytesRate OBJECT-TYPE
            SYNTAX Counter64
            MAX-ACCESS read-only
            STATUS current
            DESCRIPTION
                "Rate of matched bytes."
            ::= { hwCBQoSPolicyStatisticsClassifierEntry 11 }       

        hwCBQoSPolicyStatClassifierMatchedPassPacketsRate OBJECT-TYPE
            SYNTAX Counter64
            MAX-ACCESS read-only
            STATUS current
            DESCRIPTION
                "Rate of packets that match the traffic classifier and pass through"
            ::= { hwCBQoSPolicyStatisticsClassifierEntry 12 }
            

        hwCBQoSPolicyStatClassifierMatchedPassBytesRate OBJECT-TYPE
            SYNTAX Counter64
            MAX-ACCESS read-only
            STATUS current
            DESCRIPTION
                "Rate of bytes that match the traffic classifier and pass through"
            ::= { hwCBQoSPolicyStatisticsClassifierEntry 13 }
            

        hwCBQoSPolicyStatClassifierMatchedDropPacketsRate OBJECT-TYPE
            SYNTAX Counter64
            MAX-ACCESS read-only
            STATUS current
            DESCRIPTION
                "Rate of packets that match the traffic classification policy and are discarded"
            ::= { hwCBQoSPolicyStatisticsClassifierEntry 14 }
            

        hwCBQoSPolicyStatClassifierMatchedDropBytesRate OBJECT-TYPE
            SYNTAX Counter64
            MAX-ACCESS read-only
            STATUS current
            DESCRIPTION
                "Rate of bytes that match the traffic classification policy and are discarded"
            ::= { hwCBQoSPolicyStatisticsClassifierEntry 15 }
                                
--    Class match statistics in policy on VLAN
    hwCBQoSVlanClassMatchRunInfoTable OBJECT-TYPE
        SYNTAX SEQUENCE OF HwCBQoSVlanClassMatchRunInfoEntry
        MAX-ACCESS not-accessible
        STATUS current
        DESCRIPTION
                "A table of Running statistics for class in a QoS policy applied on VLAN."
        ::= { hwCBQoSPolicyStatisticsObjects 5 }

    
    hwCBQoSVlanClassMatchRunInfoEntry OBJECT-TYPE
        SYNTAX HwCBQoSVlanClassMatchRunInfoEntry
        MAX-ACCESS not-accessible
        STATUS current
        DESCRIPTION
                "Statistics for class in a QoS policy applied on VLAN entry."
        INDEX { hwCBQoSVlanApplyPolicyVlanId, hwCBQoSVlanApplyPolicyDirection,hwCBQoSPolicyClassIndex }
        ::= { hwCBQoSVlanClassMatchRunInfoTable 1 }

    
    HwCBQoSVlanClassMatchRunInfoEntry ::=
        SEQUENCE 
        { 
            hwCBQoSVlanClassMatchedPackets
                    Counter64,
            hwCBQoSVlanClassPassedPackets
                    Counter64,                    
            hwCBQoSVlanClassDroppedPackets
                    Counter64                      
        }

    hwCBQoSVlanClassMatchedPackets OBJECT-TYPE
        SYNTAX Counter64
        MAX-ACCESS read-only
        STATUS current
        DESCRIPTION
                "Number of packets matched the class in a policy applied on a VLAN."
        ::= { hwCBQoSVlanClassMatchRunInfoEntry 1 }

    hwCBQoSVlanClassPassedPackets OBJECT-TYPE
        SYNTAX Counter64
        MAX-ACCESS read-only
        STATUS current
        DESCRIPTION
                "Number of passed packets matched the class in a policy applied on a VLAN."
        ::= { hwCBQoSVlanClassMatchRunInfoEntry 2 }
          
    hwCBQoSVlanClassDroppedPackets OBJECT-TYPE
        SYNTAX Counter64
        MAX-ACCESS read-only
        STATUS current
        DESCRIPTION
                "Number of dropped packets matched the class in a policy applied on a VLAN."
        ::= { hwCBQoSVlanClassMatchRunInfoEntry 3 }  
                                        
--    CAR statistics in policy on VLAN
    hwCBQoSVlanCarRunInfoTable OBJECT-TYPE
        SYNTAX SEQUENCE OF HwCBQoSVlanCarRunInfoEntry
        MAX-ACCESS not-accessible
        STATUS current
        DESCRIPTION
                "A table of Running statistics for CAR statistics in policy applied on VLAN."
        ::= { hwCBQoSPolicyStatisticsObjects 6 }
    
    hwCBQoSVlanCarRunInfoEntry OBJECT-TYPE
        SYNTAX HwCBQoSVlanCarRunInfoEntry
        MAX-ACCESS not-accessible
        STATUS current
        DESCRIPTION
                "CAR statistics entry."
        INDEX { hwCBQoSVlanApplyPolicyVlanId, hwCBQoSVlanApplyPolicyDirection, hwCBQoSPolicyClassIndex }
        ::= { hwCBQoSVlanCarRunInfoTable 1 }

    
    HwCBQoSVlanCarRunInfoEntry ::=
        SEQUENCE 
        { 
            hwCBQoSVlanCarPassedPackets
                    Counter64,
            hwCBQoSVlanCarDiscardedPackets
                    Counter64
        }
    hwCBQoSVlanCarPassedPackets OBJECT-TYPE
        SYNTAX Counter64
        MAX-ACCESS read-only
        STATUS current
        DESCRIPTION
                "Number of passed packets."
        ::= { hwCBQoSVlanCarRunInfoEntry 1 }   
            
     hwCBQoSVlanCarDiscardedPackets OBJECT-TYPE
        SYNTAX Counter64
        MAX-ACCESS read-only
        STATUS current
        DESCRIPTION
                "Number of discarded packets."
        ::= { hwCBQoSVlanCarRunInfoEntry 2 }              

        -- multi-policy statistics based on policy
        hwCBQoSMultiPolicyStatisticsTable OBJECT-TYPE
            SYNTAX SEQUENCE OF HwCBQoSMultiPolicyStatisticsEntry
            MAX-ACCESS not-accessible
            STATUS current
            DESCRIPTION
                "A table of statistics for policy applied on the interface and VLAN.
                It sums up all the classes in the policy that are matched or not matched."
            ::= { hwCBQoSPolicyStatisticsObjects 7 }

        
        hwCBQoSMultiPolicyStatisticsEntry OBJECT-TYPE
            SYNTAX HwCBQoSMultiPolicyStatisticsEntry
            MAX-ACCESS not-accessible
            STATUS current
            DESCRIPTION
                "Statistics information of the policy."
            INDEX { hwCBQoSIfApplyMultiPolicyIfIndex, hwCBQoSIfApplyMultiPolicyDirection, hwCBQoSVlanApplyMultiPolicyVlanId, hwCBQoSMultiPolicyIndex }
            ::= { hwCBQoSMultiPolicyStatisticsTable 1 }

        
        HwCBQoSMultiPolicyStatisticsEntry ::=
            SEQUENCE { 
	        hwCBQoSMultiPolicyIndex
		    Integer32,
                hwCBQoSMultiPolicyMatchedPackets
                    Counter64,
                hwCBQoSMultiPolicyMatchedBytes
                    Counter64,
                hwCBQoSMultiPolicyUnmatchedPackets
                    Counter64,
                hwCBQoSMultiPolicyUnmatchedBytes
                    Counter64,
                hwCBQoSMultiPolicyMatchedPassPackets
                    Counter64,
                hwCBQoSMultiPolicyMatchedPassBytes
                    Counter64,
                hwCBQoSMultiPolicyMatchedDropPackets
                    Counter64,
                hwCBQoSMultiPolicyMatchedDropBytes
                    Counter64,
                hwCBQoSMultiPolicyResetFlag
                    EnabledStatus,
                hwCBQoSMultiPolicyMatchedPacketsRate
                    Counter64,
                hwCBQoSMultiPolicyMatchedBytesRate
                    Counter64,
                hwCBQoSMultiPolicyMatchedPassPacketsRate
                    Counter64,
                hwCBQoSMultiPolicyMatchedPassBytesRate
                    Counter64,
                hwCBQoSMultiPolicyMatchedDropPacketsRate
                    Counter64,
                hwCBQoSMultiPolicyMatchedDropBytesRate
                    Counter64,	
                hwCBQoSMultiPolicyFltPackets
                    Counter64,
                hwCBQoSMultiPolicyFltBytes
                    Counter64,
                hwCBQoSMultiPolicyFltPacketsRate
                    Counter64,
                hwCBQoSMultiPolicyFltBytesRate
                    Counter64,
                hwCBQoSMultiPolicyCarPackets
                    Counter64,
                hwCBQoSMultiPolicyCarBytes
                    Counter64,
                hwCBQoSMultiPolicyCarPacketsRate
                    Counter64,
                hwCBQoSMultiPolicyCarBytesRate
                    Counter64
             }

		hwCBQoSMultiPolicyIndex OBJECT-TYPE
            SYNTAX Integer32
            MAX-ACCESS read-only
            STATUS current
            DESCRIPTION
                "The value of this object identifies the policy index."
            ::= { hwCBQoSMultiPolicyStatisticsEntry 11 }	 
			 
        hwCBQoSMultiPolicyMatchedPackets OBJECT-TYPE
            SYNTAX Counter64
            MAX-ACCESS read-only
            STATUS current
            DESCRIPTION
                "This object indicates the number of packets matching the traffic classification policy."
            ::= { hwCBQoSMultiPolicyStatisticsEntry 12 }

        
        hwCBQoSMultiPolicyMatchedBytes OBJECT-TYPE
            SYNTAX Counter64
            MAX-ACCESS read-only
            STATUS current
            DESCRIPTION
                "This object indicates the number of bytes matching the traffic classification policy."
            ::= { hwCBQoSMultiPolicyStatisticsEntry 13 }

        
        hwCBQoSMultiPolicyUnmatchedPackets OBJECT-TYPE
            SYNTAX Counter64
            MAX-ACCESS read-only
            STATUS current
            DESCRIPTION
                "This object indicates the number of packets mismatching the traffic classification policy."
            ::= { hwCBQoSMultiPolicyStatisticsEntry 14 }

        
        hwCBQoSMultiPolicyUnmatchedBytes OBJECT-TYPE
            SYNTAX Counter64
            MAX-ACCESS read-only
            STATUS current
            DESCRIPTION
                "This object indicates the number of bytes mismatching the traffic classification policy."
            ::= { hwCBQoSMultiPolicyStatisticsEntry 15 } 

        hwCBQoSMultiPolicyMatchedPassPackets OBJECT-TYPE
            SYNTAX Counter64
            MAX-ACCESS read-only
            STATUS current
            DESCRIPTION
                "Number of packets that match the traffic classification policy and pass through"
            ::= { hwCBQoSMultiPolicyStatisticsEntry 16 }
            
        hwCBQoSMultiPolicyMatchedPassBytes OBJECT-TYPE
            SYNTAX Counter64
            MAX-ACCESS read-only
            STATUS current
            DESCRIPTION
                "Number of bytes that match the traffic classification policy and pass through"
            ::= { hwCBQoSMultiPolicyStatisticsEntry 17 }
            
        hwCBQoSMultiPolicyMatchedDropPackets OBJECT-TYPE
            SYNTAX Counter64
            MAX-ACCESS read-only
            STATUS current
            DESCRIPTION
                "Number of packets that match the traffic classification policy and are discarded"
            ::= { hwCBQoSMultiPolicyStatisticsEntry 18 }
            
        hwCBQoSMultiPolicyMatchedDropBytes OBJECT-TYPE
            SYNTAX Counter64
            MAX-ACCESS read-only
            STATUS current
            DESCRIPTION
                "Number of bytes that match the traffic classification policy and are discarded"
            ::= { hwCBQoSMultiPolicyStatisticsEntry 19 }
            
        hwCBQoSMultiPolicyResetFlag OBJECT-TYPE
            SYNTAX EnabledStatus
            MAX-ACCESS read-write
            STATUS current
            DESCRIPTION
                "Reset flag enable(1),disable(2)."
            ::= { hwCBQoSMultiPolicyStatisticsEntry 20 }
			
        hwCBQoSMultiPolicyMatchedPacketsRate OBJECT-TYPE
            SYNTAX Counter64
            MAX-ACCESS read-only
            STATUS current
            DESCRIPTION
                "Rate of matched packets"
            ::= { hwCBQoSMultiPolicyStatisticsEntry 21 }
			
        hwCBQoSMultiPolicyMatchedBytesRate OBJECT-TYPE
            SYNTAX Counter64
            MAX-ACCESS read-only
            STATUS current
            DESCRIPTION
                "Rate of matched bytes"
            ::= { hwCBQoSMultiPolicyStatisticsEntry 22 }
			
        hwCBQoSMultiPolicyMatchedPassPacketsRate OBJECT-TYPE
            SYNTAX Counter64
            MAX-ACCESS read-only
            STATUS current
            DESCRIPTION
                "Rate of matched pass packets"
            ::= { hwCBQoSMultiPolicyStatisticsEntry 23 }
			
        hwCBQoSMultiPolicyMatchedPassBytesRate OBJECT-TYPE
            SYNTAX Counter64
            MAX-ACCESS read-only
            STATUS current
            DESCRIPTION
                "Rate of matched pass bytes"
            ::= { hwCBQoSMultiPolicyStatisticsEntry 24 }	

        hwCBQoSMultiPolicyMatchedDropPacketsRate OBJECT-TYPE
            SYNTAX Counter64
            MAX-ACCESS read-only
            STATUS current
            DESCRIPTION
                "Rate of matched drop packets"
            ::= { hwCBQoSMultiPolicyStatisticsEntry 25 }
			
        hwCBQoSMultiPolicyMatchedDropBytesRate OBJECT-TYPE
            SYNTAX Counter64
            MAX-ACCESS read-only
            STATUS current
            DESCRIPTION
                "Rate of matched drop bytes"
            ::= { hwCBQoSMultiPolicyStatisticsEntry 26 }
			
        hwCBQoSMultiPolicyFltPackets OBJECT-TYPE
            SYNTAX Counter64
            MAX-ACCESS read-only
            STATUS current
            DESCRIPTION
                "Number of packets that filtered by the traffic classification policy"
            ::= { hwCBQoSMultiPolicyStatisticsEntry 27 }
			
        hwCBQoSMultiPolicyFltBytes OBJECT-TYPE
            SYNTAX Counter64
            MAX-ACCESS read-only
            STATUS current
            DESCRIPTION
                "Number of bytes that filtered by the traffic classification policy"
            ::= { hwCBQoSMultiPolicyStatisticsEntry 28 }
			
        hwCBQoSMultiPolicyFltPacketsRate OBJECT-TYPE
            SYNTAX Counter64
            MAX-ACCESS read-only
            STATUS current
            DESCRIPTION
                "Rate of filterd drop packets"
            ::= { hwCBQoSMultiPolicyStatisticsEntry 29 }
			
        hwCBQoSMultiPolicyFltBytesRate OBJECT-TYPE
            SYNTAX Counter64
            MAX-ACCESS read-only
            STATUS current
            DESCRIPTION
                "Rate of filterd drop bytes"
            ::= { hwCBQoSMultiPolicyStatisticsEntry 30 }
			
        hwCBQoSMultiPolicyCarPackets OBJECT-TYPE
            SYNTAX Counter64
            MAX-ACCESS read-only
            STATUS current
            DESCRIPTION
                "Number of packets that limited by the traffic classification policy"
            ::= { hwCBQoSMultiPolicyStatisticsEntry 31 }
			
        hwCBQoSMultiPolicyCarBytes OBJECT-TYPE
            SYNTAX Counter64
            MAX-ACCESS read-only
            STATUS current
            DESCRIPTION
                "Number of bytes that limited by the traffic classification policy"
            ::= { hwCBQoSMultiPolicyStatisticsEntry 32 }
			
        hwCBQoSMultiPolicyCarPacketsRate OBJECT-TYPE
            SYNTAX Counter64
            MAX-ACCESS read-only
            STATUS current
            DESCRIPTION
                "Rate of limited packets"
            ::= { hwCBQoSMultiPolicyStatisticsEntry 33 }
			
        hwCBQoSMultiPolicyCarBytesRate OBJECT-TYPE
            SYNTAX Counter64
            MAX-ACCESS read-only
            STATUS current
            DESCRIPTION
                "Rate of limited bytes"
            ::= { hwCBQoSMultiPolicyStatisticsEntry 34 }
			
--  class based multi-policy stat     
        hwCBQoSMultiPolicyStatisticsClassifierTable OBJECT-TYPE
            SYNTAX SEQUENCE OF HwCBQoSMultiPolicyStatisticsClassifierEntry
            MAX-ACCESS not-accessible
            STATUS current
            DESCRIPTION
                "A table of class based policy statistics."
            ::= { hwCBQoSPolicyStatisticsObjects 8 }
        
        hwCBQoSMultiPolicyStatisticsClassifierEntry OBJECT-TYPE
            SYNTAX HwCBQoSMultiPolicyStatisticsClassifierEntry
            MAX-ACCESS not-accessible
            STATUS current
            DESCRIPTION
                "Class based policy statistics entry."
            INDEX { hwCBQoSIfApplyMultiPolicyIfIndex , hwCBQoSVlanApplyMultiPolicyVlanId, hwCBQoSIfApplyMultiPolicyDirection, hwCBQoSMultiPolicyStaPolicyIndex, hwCBQoSMultiPolicyStatClassifierIndex }
            ::= { hwCBQoSMultiPolicyStatisticsClassifierTable 1 }
        
        HwCBQoSMultiPolicyStatisticsClassifierEntry ::=
            SEQUENCE { 
	        hwCBQoSMultiPolicyStaPolicyIndex
		    Integer32,                   
		hwCBQoSMultiPolicyStatClassifierIndex
		    Integer32,
                hwCBQoSMultiPolicyStatClassifierName
                    OCTET STRING,				
                hwCBQoSMultiPolicyStatClassifierMatchedPackets
                    Counter64,
                hwCBQoSMultiPolicyStatClassifierMatchedBytes
                    Counter64,
                hwCBQoSMultiPolicyStatClassifierUnmatchedPackets
                    Counter64,
                hwCBQoSMultiPolicyStatClassifierUnmatchedBytes
                    Counter64,
                hwCBQoSMultiPolicyStatClassifierMatchedPassPackets
                    Counter64,
                hwCBQoSMultiPolicyStatClassifierMatchedPassBytes
                    Counter64,
                hwCBQoSMultiPolicyStatClassifierMatchedDropPackets
                    Counter64,
                hwCBQoSMultiPolicyStatClassifierMatchedDropBytes
                    Counter64,
                hwCBQoSMultiPolicyStatClassifierMatchedPacketsRate
                    Counter64,
                hwCBQoSMultiPolicyStatClassifierMatchedBytesRate
                    Counter64,
                hwCBQoSMultiPolicyStatClassifierMatchedPassPacketsRate
                    Counter64,
                hwCBQoSMultiPolicyStatClassifierMatchedPassBytesRate
                    Counter64,
                hwCBQoSMultiPolicyStatClassifierMatchedDropPacketsRate
                    Counter64,
                hwCBQoSMultiPolicyStatClassifierMatchedDropBytesRate
                    Counter64,	
                hwCBQoSMultiPolicyStatClassifierFltPackets
                    Counter64,
                hwCBQoSMultiPolicyStatClassifierFltBytes
                    Counter64,
                hwCBQoSMultiPolicyStatClassifierFltPacketsRate
                    Counter64,
                hwCBQoSMultiPolicyStatClassifierFltBytesRate
                    Counter64,
                hwCBQoSMultiPolicyStatClassifierCarPackets
                    Counter64,
                hwCBQoSMultiPolicyStatClassifierCarBytes
                    Counter64,
                hwCBQoSMultiPolicyStatClassifierCarPacketsRate
                    Counter64,
                hwCBQoSMultiPolicyStatClassifierCarBytesRate
                    Counter64
                    }
			
	hwCBQoSMultiPolicyStaPolicyIndex OBJECT-TYPE
            SYNTAX Integer32
            MAX-ACCESS read-only
            STATUS current
            DESCRIPTION
                "The value of this object identifies the policy index."
            ::= { hwCBQoSMultiPolicyStatisticsClassifierEntry 1 }    
            
        hwCBQoSMultiPolicyStatClassifierIndex OBJECT-TYPE
            SYNTAX Integer32
            MAX-ACCESS read-only
            STATUS current
            DESCRIPTION
                "The value of this object identifies the classifier index."
            ::= { hwCBQoSMultiPolicyStatisticsClassifierEntry 2 }    
		
        hwCBQoSMultiPolicyStatClassifierName OBJECT-TYPE
            SYNTAX OCTET STRING (SIZE (1..31))
            MAX-ACCESS read-only
            STATUS current
            DESCRIPTION
                "Name of classifier."
            ::= { hwCBQoSMultiPolicyStatisticsClassifierEntry 3 }
        
        hwCBQoSMultiPolicyStatClassifierMatchedPackets OBJECT-TYPE
            SYNTAX Counter64
            MAX-ACCESS read-only
            STATUS current
            DESCRIPTION
                "Number of matched packets."
            ::= { hwCBQoSMultiPolicyStatisticsClassifierEntry 4 }
        
        hwCBQoSMultiPolicyStatClassifierMatchedBytes OBJECT-TYPE
            SYNTAX Counter64
            MAX-ACCESS read-only
            STATUS current
            DESCRIPTION
                "Number of matched bytes."
            ::= { hwCBQoSMultiPolicyStatisticsClassifierEntry 5 }
        

        hwCBQoSMultiPolicyStatClassifierUnmatchedPackets OBJECT-TYPE
            SYNTAX Counter64
            MAX-ACCESS read-only
            STATUS current
            DESCRIPTION
                "Number of unmatched packets."
            ::= { hwCBQoSMultiPolicyStatisticsClassifierEntry 6 }
        

        hwCBQoSMultiPolicyStatClassifierUnmatchedBytes OBJECT-TYPE
            SYNTAX Counter64
            MAX-ACCESS read-only
            STATUS current
            DESCRIPTION
                "Number of unmatched bytes."
            ::= { hwCBQoSMultiPolicyStatisticsClassifierEntry 7 }
        

        hwCBQoSMultiPolicyStatClassifierMatchedPassPackets OBJECT-TYPE
            SYNTAX Counter64
            MAX-ACCESS read-only
            STATUS current
            DESCRIPTION
                "Number of packets that match the traffic classifier and pass through"
            ::= { hwCBQoSMultiPolicyStatisticsClassifierEntry 8 }
            

        hwCBQoSMultiPolicyStatClassifierMatchedPassBytes OBJECT-TYPE
            SYNTAX Counter64
            MAX-ACCESS read-only
            STATUS current
            DESCRIPTION
                "Number of bytes that match the traffic classifier and pass through"
            ::= { hwCBQoSMultiPolicyStatisticsClassifierEntry 9 }
            

        hwCBQoSMultiPolicyStatClassifierMatchedDropPackets OBJECT-TYPE
            SYNTAX Counter64
            MAX-ACCESS read-only
            STATUS current
            DESCRIPTION
                "Number of packets that match the traffic classifier and discard"
            ::= { hwCBQoSMultiPolicyStatisticsClassifierEntry 10 }
            
 
        hwCBQoSMultiPolicyStatClassifierMatchedDropBytes OBJECT-TYPE
            SYNTAX Counter64
            MAX-ACCESS read-only
            STATUS current
            DESCRIPTION
                "Number of bytes that match the traffic classifier and discard"
            ::= { hwCBQoSMultiPolicyStatisticsClassifierEntry 11 }

        hwCBQoSMultiPolicyStatClassifierMatchedPacketsRate OBJECT-TYPE
            SYNTAX Counter64
            MAX-ACCESS read-only
            STATUS current
            DESCRIPTION
                "Rate of matched packets"
            ::= { hwCBQoSMultiPolicyStatisticsClassifierEntry 12 }
			
        hwCBQoSMultiPolicyStatClassifierMatchedBytesRate OBJECT-TYPE
            SYNTAX Counter64
            MAX-ACCESS read-only
            STATUS current
            DESCRIPTION
                "Rate of matched bytes"
            ::= { hwCBQoSMultiPolicyStatisticsClassifierEntry 13 }
			
        hwCBQoSMultiPolicyStatClassifierMatchedPassPacketsRate OBJECT-TYPE
            SYNTAX Counter64
            MAX-ACCESS read-only
            STATUS current
            DESCRIPTION
                "Rate of matched pass packets"
            ::= { hwCBQoSMultiPolicyStatisticsClassifierEntry 14 }
			
        hwCBQoSMultiPolicyStatClassifierMatchedPassBytesRate OBJECT-TYPE
            SYNTAX Counter64
            MAX-ACCESS read-only
            STATUS current
            DESCRIPTION
                "Rate of matched pass bytes"
            ::= { hwCBQoSMultiPolicyStatisticsClassifierEntry 15 }	

        hwCBQoSMultiPolicyStatClassifierMatchedDropPacketsRate OBJECT-TYPE
            SYNTAX Counter64
            MAX-ACCESS read-only
            STATUS current
            DESCRIPTION
                "Rate of matched drop packets"
            ::= { hwCBQoSMultiPolicyStatisticsClassifierEntry 16 }
			
        hwCBQoSMultiPolicyStatClassifierMatchedDropBytesRate OBJECT-TYPE
            SYNTAX Counter64
            MAX-ACCESS read-only
            STATUS current
            DESCRIPTION
                "Rate of matched drop bytes"
            ::= { hwCBQoSMultiPolicyStatisticsClassifierEntry 17 }
			
        hwCBQoSMultiPolicyStatClassifierFltPackets OBJECT-TYPE
            SYNTAX Counter64
            MAX-ACCESS read-only
            STATUS current
            DESCRIPTION
                "Number of packets that filtered by the traffic classification policy"
            ::= { hwCBQoSMultiPolicyStatisticsClassifierEntry 18 }
			
        hwCBQoSMultiPolicyStatClassifierFltBytes OBJECT-TYPE
            SYNTAX Counter64
            MAX-ACCESS read-only
            STATUS current
            DESCRIPTION
                "Number of bytes that filtered by the traffic classification policy"
            ::= { hwCBQoSMultiPolicyStatisticsClassifierEntry 19 }
			
        hwCBQoSMultiPolicyStatClassifierFltPacketsRate OBJECT-TYPE
            SYNTAX Counter64
            MAX-ACCESS read-only
            STATUS current
            DESCRIPTION
                "Rate of filterd drop packets"
            ::= { hwCBQoSMultiPolicyStatisticsClassifierEntry 20 }
			
        hwCBQoSMultiPolicyStatClassifierFltBytesRate OBJECT-TYPE
            SYNTAX Counter64
            MAX-ACCESS read-only
            STATUS current
            DESCRIPTION
                "Rate of filterd drop bytes"
            ::= { hwCBQoSMultiPolicyStatisticsClassifierEntry 21 }
			
        hwCBQoSMultiPolicyStatClassifierCarPackets OBJECT-TYPE
            SYNTAX Counter64
            MAX-ACCESS read-only
            STATUS current
            DESCRIPTION
                "Number of packets that limited by the traffic classification policy"
            ::= { hwCBQoSMultiPolicyStatisticsClassifierEntry 22 }
			
        hwCBQoSMultiPolicyStatClassifierCarBytes OBJECT-TYPE
            SYNTAX Counter64
            MAX-ACCESS read-only
            STATUS current
            DESCRIPTION
                "Number of bytes that limited by the traffic classification policy"
            ::= { hwCBQoSMultiPolicyStatisticsClassifierEntry 23 }
			
        hwCBQoSMultiPolicyStatClassifierCarPacketsRate OBJECT-TYPE
            SYNTAX Counter64
            MAX-ACCESS read-only
            STATUS current
            DESCRIPTION
                "Rate of limited packets"
            ::= { hwCBQoSMultiPolicyStatisticsClassifierEntry 24 }
			
        hwCBQoSMultiPolicyStatClassifierCarBytesRate OBJECT-TYPE
            SYNTAX Counter64
            MAX-ACCESS read-only
            STATUS current
            DESCRIPTION
                "Rate of limited bytes"
            ::= { hwCBQoSMultiPolicyStatisticsClassifierEntry 25 }

 --  class based subpolicy stat   
        hwCBQoSPolicyStatSubPolicyClassifierRunInfoTable OBJECT-TYPE
            SYNTAX SEQUENCE OF HwCBQoSPolicyStatSubPolicyClassifierRunInfoEntry
            MAX-ACCESS not-accessible
            STATUS current
            DESCRIPTION
                "A table of class based subpolicy statistics."
            ::= { hwCBQoSPolicyStatisticsObjects 9 }   
                    
        hwCBQoSPolicyStatSubPolicyClassifierRunInfoEntry OBJECT-TYPE
            SYNTAX HwCBQoSPolicyStatSubPolicyClassifierRunInfoEntry
            MAX-ACCESS not-accessible
            STATUS current
            DESCRIPTION
                "Class based subpolicy statistics entry."    
            INDEX { hwCBQoSIfApplyPolicyIfIndex,hwCBQoSIfVlanApplyPolicyVlanid1 ,hwCBQoSIfApplyPolicyDirection, hwCBQoSPolicyClassIndex, hwCBQoSSubPolicyClassIndex   }
            ::= { hwCBQoSPolicyStatSubPolicyClassifierRunInfoTable 1 }
        
        HwCBQoSPolicyStatSubPolicyClassifierRunInfoEntry ::=
            SEQUENCE { 
                 hwCBQoSSubPolicyClassIndex    
                    Integer32,
                hwCBQoSSubPolicyStatClassifierMatchedPackets 
                  Counter64,
                hwCBQoSSubPolicyStatClassifierMatchedBytes 
                    Counter64,
                hwCBQoSSubPolicyStatClassifierPassPackets 
                    Counter64,
                hwCBQoSSubPolicyStatClassifierPassBytes
                    Counter64,
                hwCBQoSSubPolicyStatClassifierDropPackets
                    Counter64,
                hwCBQoSSubPolicyStatClassifierDropBytes
                    Counter64,
                hwCBQoSSubPolicyStatClassifierQueueMatchedPackets
                    Counter64,
                hwCBQoSSubPolicyStatClassifierQueueMatchedBytes
                    Counter64,
                hwCBQoSSubPolicyStatClassifierQueueEnqueuedPackets
                    Counter64,
                hwCBQoSSubPolicyStatClassifierQueueEnqueuedBytes
                    Counter64,
                hwCBQoSSubPolicyStatClassifierQueueDiscardedPackets
                    Counter64,
                hwCBQoSSubPolicyStatClassifierQueueDiscardedBytes
                    Counter64,
                hwCBQoSSubPolicyStatClassifierCarGreenPackets
                    Counter64,
                hwCBQoSSubPolicyStatClassifierCarGreenBytes
                    Counter64,   
                hwCBQoSSubPolicyStatClassifierCarYellowPackets
                    Counter64,
                hwCBQoSSubPolicyStatClassifierCarYellowBytes
                    Counter64,
                hwCBQoSSubPolicyStatClassifierCarRedPackets
                    Counter64,
                hwCBQoSSubPolicyStatClassifierCarRedBytes
                    Counter64,
                hwCBQoSSubPolicyStatClassifierMatchedPacketsRate
                    Counter64,
                hwCBQoSSubPolicyStatClassifierMatchedBytesRate
                    Counter64,
                hwCBQoSSubPolicyStatClassifierMatchedPassPacketsRate
                    Counter64,
                hwCBQoSSubPolicyStatClassifierMatchedPassBytesRate
                    Counter64,
                hwCBQoSSubPolicyStatClassifierMatchedDropPacketsRate
                    Counter64,
                hwCBQoSSubPolicyStatClassifierMatchedDropBytesRate
                    Counter64,
                hwCBQoSSubPolicyStatClassifierQueueMatchedPacketsRate 
                    Counter64,
                hwCBQoSSubPolicyStatClassifierQueueMatchedBytesRate 
                    Counter64,
                hwCBQoSSubPolicyStatClassifierQueueEnqueuedPacketsRate 
                    Counter64,
                hwCBQoSSubPolicyStatClassifierQueueEnqueuedBytesRate 
                    Counter64,
                hwCBQoSSubPolicyStatClassifierQueueDiscardedPacketsRate 
                    Counter64,
                hwCBQoSSubPolicyStatClassifierQueueDiscardedBytesRate 
                    Counter64,
                hwCBQoSSubPolicyStatClassifierCarGreenPassedPacketsRate 
                    Counter64,
                hwCBQoSSubPolicyStatClassifierCarGreenPassedBytesRate 
                    Counter64,
                hwCBQoSSubPolicyStatClassifierCarYellowPassedPacketsRate 
                    Counter64,
                hwCBQoSSubPolicyStatClassifierCarYellowPassedBytesRate 
                    Counter64,
                hwCBQoSSubPolicyStatClassifierCarRedPassedPacketsRate 
                    Counter64,
                hwCBQoSSubPolicyStatClassifierCarRedPassedBytesRate 
                    Counter64,
                hwCBQoSSubPolicyClassName    
                    OCTET STRING                                         
                      }

        hwCBQoSSubPolicyClassIndex OBJECT-TYPE
            SYNTAX Integer32 
            MAX-ACCESS read-only
            STATUS current
            DESCRIPTION
                "PolicyClassIndex of subpolicy."
            ::= { hwCBQoSPolicyStatSubPolicyClassifierRunInfoEntry 1 }  
            
        hwCBQoSSubPolicyStatClassifierMatchedPackets OBJECT-TYPE
            SYNTAX Counter64
            MAX-ACCESS read-only
            STATUS current
            DESCRIPTION
                "Number of matched packets."
            ::= { hwCBQoSPolicyStatSubPolicyClassifierRunInfoEntry 2 }
        
        hwCBQoSSubPolicyStatClassifierMatchedBytes OBJECT-TYPE
            SYNTAX Counter64
            MAX-ACCESS read-only
            STATUS current
            DESCRIPTION
                "Number of matched bytes."
            ::= { hwCBQoSPolicyStatSubPolicyClassifierRunInfoEntry 3 }
        
        hwCBQoSSubPolicyStatClassifierPassPackets OBJECT-TYPE
            SYNTAX Counter64
            MAX-ACCESS read-only
            STATUS current
            DESCRIPTION
                "Number of passed packets."
            ::= { hwCBQoSPolicyStatSubPolicyClassifierRunInfoEntry 4 }
        
        hwCBQoSSubPolicyStatClassifierPassBytes OBJECT-TYPE
            SYNTAX Counter64
            MAX-ACCESS read-only
            STATUS current
            DESCRIPTION
                "Number of passed bytes."
            ::= { hwCBQoSPolicyStatSubPolicyClassifierRunInfoEntry 5 }
        
        hwCBQoSSubPolicyStatClassifierDropPackets OBJECT-TYPE
            SYNTAX Counter64
            MAX-ACCESS read-only
            STATUS current
            DESCRIPTION
                "Number of dropped packets."
            ::= { hwCBQoSPolicyStatSubPolicyClassifierRunInfoEntry 6 }
            

        hwCBQoSSubPolicyStatClassifierDropBytes OBJECT-TYPE
            SYNTAX Counter64
            MAX-ACCESS read-only
            STATUS current
            DESCRIPTION
                "Number of dropped bytes."
            ::= { hwCBQoSPolicyStatSubPolicyClassifierRunInfoEntry 7 }
            

        hwCBQoSSubPolicyStatClassifierQueueMatchedPackets OBJECT-TYPE
            SYNTAX Counter64
            MAX-ACCESS read-only
            STATUS current
            DESCRIPTION
                "Number of queue matched packets."
            ::= { hwCBQoSPolicyStatSubPolicyClassifierRunInfoEntry 8 }
            

        hwCBQoSSubPolicyStatClassifierQueueMatchedBytes OBJECT-TYPE
            SYNTAX Counter64
            MAX-ACCESS read-only
            STATUS current
            DESCRIPTION
                "Number of queue matched bytes."
            ::= { hwCBQoSPolicyStatSubPolicyClassifierRunInfoEntry 9 }

        hwCBQoSSubPolicyStatClassifierQueueEnqueuedPackets OBJECT-TYPE
            SYNTAX Counter64
            MAX-ACCESS read-only
            STATUS current
            DESCRIPTION
                "Number of queue passed packets."
            ::= { hwCBQoSPolicyStatSubPolicyClassifierRunInfoEntry 10 }
        
        hwCBQoSSubPolicyStatClassifierQueueEnqueuedBytes OBJECT-TYPE
            SYNTAX Counter64
            MAX-ACCESS read-only
            STATUS current
            DESCRIPTION
                "Number of queue passed bytes."
            ::= { hwCBQoSPolicyStatSubPolicyClassifierRunInfoEntry 11 }       

        hwCBQoSSubPolicyStatClassifierQueueDiscardedPackets OBJECT-TYPE
            SYNTAX Counter64
            MAX-ACCESS read-only
            STATUS current
            DESCRIPTION
                "Number of queue dropped packets."
            ::= { hwCBQoSPolicyStatSubPolicyClassifierRunInfoEntry 12 }
            
        hwCBQoSSubPolicyStatClassifierQueueDiscardedBytes OBJECT-TYPE
            SYNTAX Counter64
            MAX-ACCESS read-only
            STATUS current
            DESCRIPTION
                "Number of queue dropped bytes."
            ::= { hwCBQoSPolicyStatSubPolicyClassifierRunInfoEntry 13 }
            
        hwCBQoSSubPolicyStatClassifierCarGreenPackets OBJECT-TYPE
            SYNTAX Counter64
            MAX-ACCESS read-only
            STATUS current
            DESCRIPTION
                "Number of green packets."
            ::= { hwCBQoSPolicyStatSubPolicyClassifierRunInfoEntry 14 }
            
        hwCBQoSSubPolicyStatClassifierCarGreenBytes OBJECT-TYPE
            SYNTAX Counter64
            MAX-ACCESS read-only
            STATUS current
            DESCRIPTION
                "Number of green bytes."
            ::= { hwCBQoSPolicyStatSubPolicyClassifierRunInfoEntry 15 }

        hwCBQoSSubPolicyStatClassifierCarYellowPackets OBJECT-TYPE
            SYNTAX Counter64
            MAX-ACCESS read-only
            STATUS current
            DESCRIPTION
                "Number of yellow packets."
            ::= { hwCBQoSPolicyStatSubPolicyClassifierRunInfoEntry 16 }  
            
        hwCBQoSSubPolicyStatClassifierCarYellowBytes OBJECT-TYPE
            SYNTAX Counter64
            MAX-ACCESS read-only
            STATUS current
            DESCRIPTION
                "Number of yellow bytes."
            ::= { hwCBQoSPolicyStatSubPolicyClassifierRunInfoEntry 17 }
            
        hwCBQoSSubPolicyStatClassifierCarRedPackets OBJECT-TYPE
            SYNTAX Counter64
            MAX-ACCESS read-only
            STATUS current
            DESCRIPTION
                "Number of red packets."
            ::= { hwCBQoSPolicyStatSubPolicyClassifierRunInfoEntry 18 }   
            
        hwCBQoSSubPolicyStatClassifierCarRedBytes OBJECT-TYPE
            SYNTAX Counter64
            MAX-ACCESS read-only
            STATUS current
            DESCRIPTION
                "Number of red bytes."
            ::= { hwCBQoSPolicyStatSubPolicyClassifierRunInfoEntry 19 }

        hwCBQoSSubPolicyStatClassifierMatchedPacketsRate OBJECT-TYPE
            SYNTAX Counter64
            MAX-ACCESS read-only
            STATUS current
            DESCRIPTION
                "Rate of matched packets."
            ::= { hwCBQoSPolicyStatSubPolicyClassifierRunInfoEntry 20 }

        hwCBQoSSubPolicyStatClassifierMatchedBytesRate OBJECT-TYPE
            SYNTAX Counter64
            MAX-ACCESS read-only
            STATUS current
            DESCRIPTION
                "Rate of matched bytes."
            ::= { hwCBQoSPolicyStatSubPolicyClassifierRunInfoEntry 21 } 
            
        hwCBQoSSubPolicyStatClassifierMatchedPassPacketsRate OBJECT-TYPE
            SYNTAX Counter64
            MAX-ACCESS read-only
            STATUS current
            DESCRIPTION
                "Rate of passed packets."
            ::= { hwCBQoSPolicyStatSubPolicyClassifierRunInfoEntry 22 }   
            
        hwCBQoSSubPolicyStatClassifierMatchedPassBytesRate OBJECT-TYPE
            SYNTAX Counter64
            MAX-ACCESS read-only
            STATUS current
            DESCRIPTION
                "Rate of passed bytes."
            ::= { hwCBQoSPolicyStatSubPolicyClassifierRunInfoEntry 23 }

        hwCBQoSSubPolicyStatClassifierMatchedDropPacketsRate OBJECT-TYPE
            SYNTAX Counter64
            MAX-ACCESS read-only
            STATUS current
            DESCRIPTION
                "Rate of dropped packets."
            ::= { hwCBQoSPolicyStatSubPolicyClassifierRunInfoEntry 24 }

        hwCBQoSSubPolicyStatClassifierMatchedDropBytesRate OBJECT-TYPE
            SYNTAX Counter64
            MAX-ACCESS read-only
            STATUS current
            DESCRIPTION
                "Rate of dropped bytes."
            ::= { hwCBQoSPolicyStatSubPolicyClassifierRunInfoEntry 25 }

        hwCBQoSSubPolicyStatClassifierQueueMatchedPacketsRate OBJECT-TYPE
            SYNTAX Counter64
            MAX-ACCESS read-only
            STATUS current
            DESCRIPTION
                "Rate of queue matched packets."
            ::= { hwCBQoSPolicyStatSubPolicyClassifierRunInfoEntry 26 }

        hwCBQoSSubPolicyStatClassifierQueueMatchedBytesRate OBJECT-TYPE
            SYNTAX Counter64
            MAX-ACCESS read-only
            STATUS current
            DESCRIPTION
                "Rate of queue matched bytes."
            ::= { hwCBQoSPolicyStatSubPolicyClassifierRunInfoEntry 27 }

        hwCBQoSSubPolicyStatClassifierQueueEnqueuedPacketsRate OBJECT-TYPE
            SYNTAX Counter64
            MAX-ACCESS read-only
            STATUS current
            DESCRIPTION
                "Rate of queue passed packets."
            ::= { hwCBQoSPolicyStatSubPolicyClassifierRunInfoEntry 28 }

        hwCBQoSSubPolicyStatClassifierQueueEnqueuedBytesRate OBJECT-TYPE
            SYNTAX Counter64
            MAX-ACCESS read-only
            STATUS current
            DESCRIPTION
                "Rate of queue passed bytes."
            ::= { hwCBQoSPolicyStatSubPolicyClassifierRunInfoEntry 29 }

        hwCBQoSSubPolicyStatClassifierQueueDiscardedPacketsRate OBJECT-TYPE
            SYNTAX Counter64
            MAX-ACCESS read-only
            STATUS current
            DESCRIPTION
                "Rate of queue dropped packets."
            ::= { hwCBQoSPolicyStatSubPolicyClassifierRunInfoEntry 30 }

        hwCBQoSSubPolicyStatClassifierQueueDiscardedBytesRate OBJECT-TYPE
            SYNTAX Counter64
            MAX-ACCESS read-only
            STATUS current
            DESCRIPTION
                "Rate of queue dropped bytes."
            ::= { hwCBQoSPolicyStatSubPolicyClassifierRunInfoEntry 31 }

        hwCBQoSSubPolicyStatClassifierCarGreenPassedPacketsRate OBJECT-TYPE
            SYNTAX Counter64
            MAX-ACCESS read-only
            STATUS current
            DESCRIPTION
                "Rate of green packets."
            ::= { hwCBQoSPolicyStatSubPolicyClassifierRunInfoEntry 32 }

        hwCBQoSSubPolicyStatClassifierCarGreenPassedBytesRate OBJECT-TYPE
            SYNTAX Counter64
            MAX-ACCESS read-only
            STATUS current
            DESCRIPTION
                "Rate of green bytes."
            ::= { hwCBQoSPolicyStatSubPolicyClassifierRunInfoEntry 33 }  
            
        hwCBQoSSubPolicyStatClassifierCarYellowPassedPacketsRate  OBJECT-TYPE
            SYNTAX Counter64
            MAX-ACCESS read-only
            STATUS current
            DESCRIPTION
                "Rate of yellow packets."
            ::= { hwCBQoSPolicyStatSubPolicyClassifierRunInfoEntry 34 }
  
        hwCBQoSSubPolicyStatClassifierCarYellowPassedBytesRate OBJECT-TYPE
            SYNTAX Counter64
            MAX-ACCESS read-only
            STATUS current
            DESCRIPTION
                "Rate of yellow bytes."
            ::= { hwCBQoSPolicyStatSubPolicyClassifierRunInfoEntry 35 }    
            
        hwCBQoSSubPolicyStatClassifierCarRedPassedPacketsRate  OBJECT-TYPE
            SYNTAX Counter64
            MAX-ACCESS read-only
            STATUS current
            DESCRIPTION
                "Rate of red bytes."
            ::= { hwCBQoSPolicyStatSubPolicyClassifierRunInfoEntry 36 }
            
        hwCBQoSSubPolicyStatClassifierCarRedPassedBytesRate  OBJECT-TYPE
            SYNTAX Counter64
            MAX-ACCESS read-only
            STATUS current
            DESCRIPTION
                "Rate of red bytes."
            ::= { hwCBQoSPolicyStatSubPolicyClassifierRunInfoEntry 37 }
      
        hwCBQoSSubPolicyClassName OBJECT-TYPE
            SYNTAX OCTET STRING (SIZE (1..31))
            MAX-ACCESS read-only
            STATUS current
            DESCRIPTION
                "Name of sub classifier."
            ::= { hwCBQoSPolicyStatSubPolicyClassifierRunInfoEntry 38 }              
--  Global Policy car statistics     
        hwCBQoSGlobalCarStatisticsTable OBJECT-TYPE
            SYNTAX SEQUENCE OF HwCBQoSGlobalCarStatisticsEntry
            MAX-ACCESS not-accessible
            STATUS current
            DESCRIPTION
                "This table is applied to global ACL.This table describes CAR statistics for class-based traffic classification. ."
            ::= { hwCBQoSPolicyStatisticsObjects 10 }

        
        hwCBQoSGlobalCarStatisticsEntry OBJECT-TYPE
            SYNTAX HwCBQoSGlobalCarStatisticsEntry
            MAX-ACCESS not-accessible
            STATUS current
            DESCRIPTION
                "A table of CAR statistics for class-based traffic classification applied
                in traffic monitoring, including the statistics of  packets that have the
                rate within CIR, of CIR, of PIR or exceeds PIR."
            INDEX { hwCBQoSGlobalCarApplyType, hwCBQoSGlobalCarDirection, hwCBQoSGlobalCarSlotId, hwCBQoSGlobalCarClassifierName }
            ::= { hwCBQoSGlobalCarStatisticsTable 1 }

        
        HwCBQoSGlobalCarStatisticsEntry ::=
            SEQUENCE { 
                hwCBQoSGlobalCarSlotId
                    Integer32,
				hwCBQoSGlobalCarApplyType
                    PolicyApplyType,
                hwCBQoSGlobalCarDirection
                    INTEGER,
                hwCBQoSGlobalCarClassifierName
                    OCTET STRING,
                hwCBQoSGlobalCarConformedPackets
                    Counter64,
                hwCBQoSGlobalCarConformedBytes
                    Counter64,
                hwCBQoSGlobalCarConformedPacketRate
                    Counter64,
                hwCBQoSGlobalCarConformedByteRate
                    Counter64,
                hwCBQoSGlobalCarExceededPackets
                    Counter64,
                hwCBQoSGlobalCarExceededBytes
                    Counter64,
                hwCBQoSGlobalCarExceededPacketRate
                    Counter64,
                hwCBQoSGlobalCarExceededByteRate
                    Counter64,
                hwCBQoSGlobalCarOverflowPackets
                    Counter64,
                hwCBQoSGlobalCarOverflowBytes
                    Counter64,
                hwCBQoSGlobalCarOverflowPacketRate
                    Counter64,
                hwCBQoSGlobalCarOverflowByteRate
                    Counter64,
                hwCBQoSGlobalCarPassedPackets
                    Counter64,
                hwCBQoSGlobalCarPassedBytes
                    Counter64,
                hwCBQoSGlobalCarDroppedPackets
                    Counter64,
                hwCBQoSGlobalCarDroppedBytes
                    Counter64
             }

        hwCBQoSGlobalCarSlotId OBJECT-TYPE
            SYNTAX Integer32 (0..128)
            MAX-ACCESS read-only
            STATUS current
            DESCRIPTION
                "The ID of the slot that the interface is located."
            ::= { hwCBQoSGlobalCarStatisticsEntry 1 }


        hwCBQoSGlobalCarApplyType OBJECT-TYPE
            SYNTAX PolicyApplyType
            MAX-ACCESS read-only
            STATUS current
            DESCRIPTION
                "The type of car applied in global."
            ::= { hwCBQoSGlobalCarStatisticsEntry 2 }


        hwCBQoSGlobalCarDirection OBJECT-TYPE
            SYNTAX INTEGER
                {
                inbound(1),
                outbound(2)
                }
            MAX-ACCESS read-only
            STATUS current
            DESCRIPTION
                "This object indicates the direction where the CAR statistics are queried."
            ::= { hwCBQoSGlobalCarStatisticsEntry 3 }


        hwCBQoSGlobalCarClassifierName OBJECT-TYPE
            SYNTAX OCTET STRING (SIZE (1..31))
            MAX-ACCESS read-only
            STATUS current
            DESCRIPTION
                "The name of classifier."
            ::= { hwCBQoSGlobalCarStatisticsEntry 4 }


        hwCBQoSGlobalCarConformedPackets OBJECT-TYPE
            SYNTAX Counter64
            MAX-ACCESS read-only
            STATUS current
            DESCRIPTION
                "This object indicates the number of packets within the range of CIR."
            ::= { hwCBQoSGlobalCarStatisticsEntry 5 }

        
        hwCBQoSGlobalCarConformedBytes OBJECT-TYPE
            SYNTAX Counter64
            MAX-ACCESS read-only
            STATUS current
            DESCRIPTION
                "This object indicates the number of bytes within the range of CIR."
            ::= { hwCBQoSGlobalCarStatisticsEntry 6 }

        
        hwCBQoSGlobalCarConformedPacketRate OBJECT-TYPE
            SYNTAX Counter64
            MAX-ACCESS read-only
            STATUS current
            DESCRIPTION
                "This object indicates the packet rate within the range of CIR, in pps."
            ::= { hwCBQoSGlobalCarStatisticsEntry 7 }

        
        hwCBQoSGlobalCarConformedByteRate OBJECT-TYPE
            SYNTAX Counter64
            MAX-ACCESS read-only
            STATUS current
            DESCRIPTION
                "This object indicates the bytes rate within the range of CIR, in Bps."
            ::= { hwCBQoSGlobalCarStatisticsEntry 8 }

        
        hwCBQoSGlobalCarExceededPackets OBJECT-TYPE
            SYNTAX Counter64
            MAX-ACCESS read-only
            STATUS current
            DESCRIPTION
                "This object indicates the number of packets between PIR and CIR."
            ::= { hwCBQoSGlobalCarStatisticsEntry 9 }

        
        hwCBQoSGlobalCarExceededBytes OBJECT-TYPE
            SYNTAX Counter64
            MAX-ACCESS read-only
            STATUS current
            DESCRIPTION
                "This object indicates the number of bytes between PIR and CIR."
            ::= { hwCBQoSGlobalCarStatisticsEntry 10 }

        
        hwCBQoSGlobalCarExceededPacketRate OBJECT-TYPE
            SYNTAX Counter64
            MAX-ACCESS read-only
            STATUS current
            DESCRIPTION
                "This object indicates the packet rate between PIR and CIR, in pps."
            ::= { hwCBQoSGlobalCarStatisticsEntry 11 }

        
        hwCBQoSGlobalCarExceededByteRate OBJECT-TYPE
            SYNTAX Counter64
            MAX-ACCESS read-only
            STATUS current
            DESCRIPTION
                "This object indicates the byte rate between PIR and CIR, in Bps."
            ::= { hwCBQoSGlobalCarStatisticsEntry 12 }

        
        hwCBQoSGlobalCarOverflowPackets OBJECT-TYPE
            SYNTAX Counter64
            MAX-ACCESS read-only
            STATUS current
            DESCRIPTION
                "This object indicates the rate of packets that exceeds the PIR."
            ::= { hwCBQoSGlobalCarStatisticsEntry 13 }

        
        hwCBQoSGlobalCarOverflowBytes OBJECT-TYPE
            SYNTAX Counter64
            MAX-ACCESS read-only
            STATUS current
            DESCRIPTION
                "This object indicates the number of bytes when PIR is exceeded."
            ::= { hwCBQoSGlobalCarStatisticsEntry 14 }

        
        hwCBQoSGlobalCarOverflowPacketRate OBJECT-TYPE
            SYNTAX Counter64
            MAX-ACCESS read-only
            STATUS current
            DESCRIPTION
                "This object indicates the rate of packets that exceeds the PIR."
            ::= { hwCBQoSGlobalCarStatisticsEntry 15 }

        
        hwCBQoSGlobalCarOverflowByteRate OBJECT-TYPE
            SYNTAX Counter64
            MAX-ACCESS read-only
            STATUS current
            DESCRIPTION
                "This object indicates the rate of bytes that exceeds the PIR, in Bps."
            ::= { hwCBQoSGlobalCarStatisticsEntry 16 }

        
        hwCBQoSGlobalCarPassedPackets OBJECT-TYPE
            SYNTAX Counter64
            MAX-ACCESS read-only
            STATUS current
            DESCRIPTION
                "This object indicates the number of packets passed after the Committed Access Rate (CAR) is set."
            ::= { hwCBQoSGlobalCarStatisticsEntry 17 }
			 
        hwCBQoSGlobalCarPassedBytes OBJECT-TYPE
            SYNTAX Counter64
            MAX-ACCESS read-only
            STATUS current
            DESCRIPTION
                "This object indicates the number of the bytes passed after CAR is set."
            ::= { hwCBQoSGlobalCarStatisticsEntry 18 }

        
        hwCBQoSGlobalCarDroppedPackets OBJECT-TYPE
            SYNTAX Counter64
            MAX-ACCESS read-only
            STATUS current
            DESCRIPTION
                "This object indicates the number of discarded packets after CAR is set."
            ::= { hwCBQoSGlobalCarStatisticsEntry 19 }

        hwCBQoSGlobalCarDroppedBytes OBJECT-TYPE
            SYNTAX Counter64
            MAX-ACCESS read-only
            STATUS current
            DESCRIPTION
                "This object indicates the number of discarded packets after CAR is set."
            ::= { hwCBQoSGlobalCarStatisticsEntry 20 }			
        
		
-- Global policy statics
        hwCBQoSGlobalPolicyStatisticsTable OBJECT-TYPE
            SYNTAX SEQUENCE OF HwCBQoSGlobalPolicyStatisticsEntry
            MAX-ACCESS not-accessible
            STATUS current
            DESCRIPTION
                "This table is applied to global ACL.This table describes policy-based traffic classification statistics. ."
            ::= { hwCBQoSPolicyStatisticsObjects 11 }

        
        hwCBQoSGlobalPolicyStatisticsEntry OBJECT-TYPE
            SYNTAX HwCBQoSGlobalPolicyStatisticsEntry
            MAX-ACCESS not-accessible
            STATUS current
            DESCRIPTION
                "Statistics information of the policy."
            INDEX { hwCBQoSGlobalPolicyApplyType, hwCBQoSGlobalPolicyDirection, hwCBQoSGlobalPolicySlotId }
            ::= { hwCBQoSGlobalPolicyStatisticsTable 1 }

        
        HwCBQoSGlobalPolicyStatisticsEntry ::=
            SEQUENCE { 
                hwCBQoSGlobalPolicySlotId
                    Integer32,
				hwCBQoSGlobalPolicyApplyType
                    PolicyApplyType,
                hwCBQoSGlobalPolicyDirection
                    INTEGER,
                hwCBQoSGlobalPolicyMatchedPackets
                    Counter64,
                hwCBQoSGlobalPolicyMatchedBytes
                    Counter64,
                hwCBQoSGlobalPolicyUnmatchedPackets
                    Counter64,
                hwCBQoSGlobalPolicyUnmatchedBytes
                    Counter64,
                hwCBQoSGlobalPolicyMatchedPassPackets
                    Counter64,
                hwCBQoSGlobalPolicyMatchedPassBytes
                    Counter64,
                hwCBQoSGlobalPolicyMatchedDropPackets
                    Counter64,
                hwCBQoSGlobalPolicyMatchedDropBytes
                    Counter64,
                hwCBQoSGlobalPolicyResetFlag
                    EnabledStatus					
             }


        hwCBQoSGlobalPolicySlotId OBJECT-TYPE
            SYNTAX Integer32 (0..128)
            MAX-ACCESS read-only
            STATUS current
            DESCRIPTION
                "The ID of the slot that the interface is located."
            ::= { hwCBQoSGlobalPolicyStatisticsEntry 1 }


        hwCBQoSGlobalPolicyApplyType OBJECT-TYPE
            SYNTAX PolicyApplyType
            MAX-ACCESS read-only
            STATUS current
            DESCRIPTION
                "The type of car."
            ::= { hwCBQoSGlobalPolicyStatisticsEntry 2 }


        hwCBQoSGlobalPolicyDirection OBJECT-TYPE
            SYNTAX INTEGER
                {
                inbound(1),
                outbound(2)
                }
            MAX-ACCESS read-only
            STATUS current
            DESCRIPTION
                "This object indicates the direction where the CAR statistics are queried."
            ::= { hwCBQoSGlobalPolicyStatisticsEntry 3 }
	    
	    
	hwCBQoSGlobalPolicyMatchedPackets OBJECT-TYPE
            SYNTAX Counter64
            MAX-ACCESS read-only
            STATUS current
            DESCRIPTION
                "This object indicates the number of packets matching the traffic classification policy."
            ::= { hwCBQoSGlobalPolicyStatisticsEntry 4 }

        
        hwCBQoSGlobalPolicyMatchedBytes OBJECT-TYPE
            SYNTAX Counter64
            MAX-ACCESS read-only
            STATUS current
            DESCRIPTION
                "This object indicates the number of bytes matching the traffic classification policy."
            ::= { hwCBQoSGlobalPolicyStatisticsEntry 5 }

        
        hwCBQoSGlobalPolicyUnmatchedPackets OBJECT-TYPE
            SYNTAX Counter64
            MAX-ACCESS read-only
            STATUS current
            DESCRIPTION
                "This object indicates the number of packets mismatching the traffic classification policy."
            ::= { hwCBQoSGlobalPolicyStatisticsEntry 6 }

        
        hwCBQoSGlobalPolicyUnmatchedBytes OBJECT-TYPE
            SYNTAX Counter64
            MAX-ACCESS read-only
            STATUS current
            DESCRIPTION
                "This object indicates the number of bytes mismatching the traffic classification policy."
            ::= { hwCBQoSGlobalPolicyStatisticsEntry 7 } 

        hwCBQoSGlobalPolicyMatchedPassPackets OBJECT-TYPE
            SYNTAX Counter64
            MAX-ACCESS read-only
            STATUS current
            DESCRIPTION
                "Number of packets that match the traffic classification policy and pass through"
            ::= { hwCBQoSGlobalPolicyStatisticsEntry 8 }
            
        hwCBQoSGlobalPolicyMatchedPassBytes OBJECT-TYPE
            SYNTAX Counter64
            MAX-ACCESS read-only
            STATUS current
            DESCRIPTION
                "Number of bytes that match the traffic classification policy and pass through"
            ::= { hwCBQoSGlobalPolicyStatisticsEntry 9 }
            
        hwCBQoSGlobalPolicyMatchedDropPackets OBJECT-TYPE
            SYNTAX Counter64
            MAX-ACCESS read-only
            STATUS current
            DESCRIPTION
                "Number of packets that match the traffic classification policy and are discarded"
            ::= { hwCBQoSGlobalPolicyStatisticsEntry 10 }
            
        hwCBQoSGlobalPolicyMatchedDropBytes OBJECT-TYPE
            SYNTAX Counter64
            MAX-ACCESS read-only
            STATUS current
            DESCRIPTION
                "Number of bytes that match the traffic classification policy and are discarded"
            ::= { hwCBQoSGlobalPolicyStatisticsEntry 11 }
            
        hwCBQoSGlobalPolicyResetFlag OBJECT-TYPE
            SYNTAX EnabledStatus
            MAX-ACCESS read-write
            STATUS current
            DESCRIPTION
                "Reset flag enable(1),disable(2)."
            ::= { hwCBQoSGlobalPolicyStatisticsEntry 12 }



--  Global classifier statistics
        hwCBQoSGlobalClassifierStatisticsTable OBJECT-TYPE
            SYNTAX SEQUENCE OF HwCBQoSGlobalClassifierStatisticsEntry
            MAX-ACCESS not-accessible
            STATUS current
            DESCRIPTION
                " This table is applied to global ACL.This table describes class-based traffic classification statistics."
            ::= { hwCBQoSPolicyStatisticsObjects 12 }
            
        hwCBQoSGlobalClassifierStatisticsEntry OBJECT-TYPE
            SYNTAX HwCBQoSGlobalClassifierStatisticsEntry
            MAX-ACCESS not-accessible
            STATUS current
            DESCRIPTION
                "Statistics information of the class."
            INDEX { hwCBQoSGlobalClassifierApplyType, hwCBQoSGlobalClassifierDirection, hwCBQoSGlobalClassifierSlotId, hwCBQoSGlobalClassifierClassifierName }
            ::= { hwCBQoSGlobalClassifierStatisticsTable 1 }

        
        HwCBQoSGlobalClassifierStatisticsEntry ::=
            SEQUENCE {
				hwCBQoSGlobalClassifierSlotId
                    Integer32,
				hwCBQoSGlobalClassifierApplyType
                    PolicyApplyType,
                hwCBQoSGlobalClassifierDirection
                    INTEGER,
                hwCBQoSGlobalClassifierClassifierName
                    OCTET STRING,
                hwCBQoSGlobalClassifierMatchedPackets
                    Counter64,
                hwCBQoSGlobalClassifierMatchedBytes
                    Counter64,
                hwCBQoSGlobalClassifierMatchedPassPackets
                    Counter64,
                hwCBQoSGlobalClassifierMatchedPassBytes
                    Counter64,
                hwCBQoSGlobalClassifierMatchedDropPackets
                    Counter64,
                hwCBQoSGlobalClassifierMatchedDropBytes
                    Counter64
             }
			 
                  
        hwCBQoSGlobalClassifierSlotId OBJECT-TYPE
            SYNTAX Integer32 (0..128)
            MAX-ACCESS read-only
            STATUS current
            DESCRIPTION
                "The ID of the slot that the interface is located."
            ::= { hwCBQoSGlobalClassifierStatisticsEntry 1 }


        hwCBQoSGlobalClassifierApplyType OBJECT-TYPE
            SYNTAX PolicyApplyType
            MAX-ACCESS read-only
            STATUS current
            DESCRIPTION
                "The type of car."
            ::= { hwCBQoSGlobalClassifierStatisticsEntry 2 }


        hwCBQoSGlobalClassifierDirection OBJECT-TYPE
            SYNTAX INTEGER
                {
                inbound(1),
                outbound(2)
                }
            MAX-ACCESS read-only
            STATUS current
            DESCRIPTION
                "This object indicates the direction where the CAR statistics are queried."
            ::= { hwCBQoSGlobalClassifierStatisticsEntry 3 }


        hwCBQoSGlobalClassifierClassifierName OBJECT-TYPE
            SYNTAX OCTET STRING (SIZE (1..31))
            MAX-ACCESS read-only
            STATUS current
            DESCRIPTION
                "The name of classifier."
            ::= { hwCBQoSGlobalClassifierStatisticsEntry 4 }
	      
	      
	hwCBQoSGlobalClassifierMatchedPackets OBJECT-TYPE
            SYNTAX Counter64
            MAX-ACCESS read-only
            STATUS current
            DESCRIPTION
                "Indicates the number of packets that match the class."
            ::= { hwCBQoSGlobalClassifierStatisticsEntry 5 }

        
        hwCBQoSGlobalClassifierMatchedBytes OBJECT-TYPE
            SYNTAX Counter64
            MAX-ACCESS read-only
            STATUS current
            DESCRIPTION
                "Indicates the number of matched bytes."
            ::= { hwCBQoSGlobalClassifierStatisticsEntry 6 }     
        
        hwCBQoSGlobalClassifierMatchedPassPackets OBJECT-TYPE
            SYNTAX Counter64
            MAX-ACCESS read-only
            STATUS current
            DESCRIPTION
                "Indicates the matched and passed traffic in packets."
            ::= { hwCBQoSGlobalClassifierStatisticsEntry 7 }
            
        hwCBQoSGlobalClassifierMatchedPassBytes OBJECT-TYPE
            SYNTAX Counter64
            MAX-ACCESS read-only
            STATUS current
            DESCRIPTION
                "Indicates the matched and passed traffic in bytes."
            ::= { hwCBQoSGlobalClassifierStatisticsEntry 8 }
            
        hwCBQoSGlobalClassifierMatchedDropPackets OBJECT-TYPE
            SYNTAX Counter64
            MAX-ACCESS read-only
            STATUS current
            DESCRIPTION
                "Indicates the matched and discarded traffic in packets."
            ::= { hwCBQoSGlobalClassifierStatisticsEntry 9 }
            
        hwCBQoSGlobalClassifierMatchedDropBytes OBJECT-TYPE
            SYNTAX Counter64
            MAX-ACCESS read-only
            STATUS current
            DESCRIPTION
                "Indicates the matched and discarded traffic in bytes."
            ::= { hwCBQoSGlobalClassifierStatisticsEntry 10 }            

-- multi-policy applied on global statistics based on policy
        hwCBQoSGlobalMultiPolicyStatisticsTable OBJECT-TYPE
            SYNTAX SEQUENCE OF HwCBQoSGlobalMultiPolicyStatisticsEntry
            MAX-ACCESS not-accessible
            STATUS current
            DESCRIPTION
                "A table of statistics for policy applied on global.
                It sums up all the classes in the policy that are matched."
            ::= { hwCBQoSPolicyStatisticsObjects 13 }

        
        hwCBQoSGlobalMultiPolicyStatisticsEntry OBJECT-TYPE
            SYNTAX HwCBQoSGlobalMultiPolicyStatisticsEntry
            MAX-ACCESS not-accessible
            STATUS current
            DESCRIPTION
                "Statistics information of the policy."
            INDEX { hwCBQoSGlobalApplyMultiPolicyChassisId, hwCBQoSGlobalApplyMultiPolicySlotId, hwCBQoSGlobalApplyMultiPolicyDirection, hwCBQoSGlobalApplyMultiPolicyIndex }
            ::= { hwCBQoSGlobalMultiPolicyStatisticsTable 1 }

        
        HwCBQoSGlobalMultiPolicyStatisticsEntry ::=
            SEQUENCE {
                hwCBQoSGlobalMultiPolicyMatchedPackets
                    Counter64,
                hwCBQoSGlobalMultiPolicyMatchedBytes
                    Counter64,
                hwCBQoSGlobalMultiPolicyMatchedPassPackets
                    Counter64,
                hwCBQoSGlobalMultiPolicyMatchedPassBytes
                    Counter64,
                hwCBQoSGlobalMultiPolicyMatchedDropPackets
                    Counter64,
                hwCBQoSGlobalMultiPolicyMatchedDropBytes
                    Counter64,
                hwCBQoSGlobalMultiPolicyResetFlag
                    EnabledStatus        
             }
			 
        hwCBQoSGlobalMultiPolicyMatchedPackets OBJECT-TYPE
            SYNTAX Counter64
            MAX-ACCESS read-only
            STATUS current
            DESCRIPTION
                "This object indicates the number of packets matching the traffic policy."
            ::= { hwCBQoSGlobalMultiPolicyStatisticsEntry 1 }

        
        hwCBQoSGlobalMultiPolicyMatchedBytes OBJECT-TYPE
            SYNTAX Counter64
            MAX-ACCESS read-only
            STATUS current
            DESCRIPTION
                "This object indicates the number of bytes matching the traffic policy."
            ::= { hwCBQoSGlobalMultiPolicyStatisticsEntry 2 }
  
        hwCBQoSGlobalMultiPolicyMatchedPassPackets OBJECT-TYPE
            SYNTAX Counter64
            MAX-ACCESS read-only
            STATUS current
            DESCRIPTION
                "Number of packets that match the traffic classification policy and pass through"
            ::= { hwCBQoSGlobalMultiPolicyStatisticsEntry 3 }
            
        hwCBQoSGlobalMultiPolicyMatchedPassBytes OBJECT-TYPE
            SYNTAX Counter64
            MAX-ACCESS read-only
            STATUS current
            DESCRIPTION
                "Number of bytes that match the traffic classification policy and pass through"
            ::= { hwCBQoSGlobalMultiPolicyStatisticsEntry 4 }
            
        hwCBQoSGlobalMultiPolicyMatchedDropPackets OBJECT-TYPE
            SYNTAX Counter64
            MAX-ACCESS read-only
            STATUS current
            DESCRIPTION
                "Number of packets that match the traffic classification policy and are discarded"
            ::= { hwCBQoSGlobalMultiPolicyStatisticsEntry 5 }
            
        hwCBQoSGlobalMultiPolicyMatchedDropBytes OBJECT-TYPE
            SYNTAX Counter64
            MAX-ACCESS read-only
            STATUS current
            DESCRIPTION
                "Number of bytes that match the traffic classification policy and are discarded"
            ::= { hwCBQoSGlobalMultiPolicyStatisticsEntry 6 }
            
        hwCBQoSGlobalMultiPolicyResetFlag OBJECT-TYPE
            SYNTAX EnabledStatus
            MAX-ACCESS read-write
            STATUS current
            DESCRIPTION
                "Reset flag enable(1),disable(2)."
            ::= { hwCBQoSGlobalMultiPolicyStatisticsEntry 7 }

--  class based multi-policy applied on global stat     
        hwCBQoSGlobalMultiPolicyStatisticsClassifierTable OBJECT-TYPE
            SYNTAX SEQUENCE OF HwCBQoSGlobalMultiPolicyStatisticsClassifierEntry
            MAX-ACCESS not-accessible
            STATUS current
            DESCRIPTION
                "A table of class based policy statistics."
            ::= { hwCBQoSPolicyStatisticsObjects 14 }
        
        hwCBQoSGlobalMultiPolicyStatisticsClassifierEntry OBJECT-TYPE
            SYNTAX HwCBQoSGlobalMultiPolicyStatisticsClassifierEntry
            MAX-ACCESS not-accessible
            STATUS current
            DESCRIPTION
                "Class based policy statistics entry."
            INDEX { hwCBQoSGlobalApplyMultiPolicyChassisId, hwCBQoSGlobalApplyMultiPolicySlotId, hwCBQoSGlobalApplyMultiPolicyDirection, hwCBQoSGlobalApplyMultiPolicyIndex, hwCBQoSGlobalMultiPolicyStatClassifierIndex }
            ::= { hwCBQoSGlobalMultiPolicyStatisticsClassifierTable 1 }
        
        HwCBQoSGlobalMultiPolicyStatisticsClassifierEntry ::=
            SEQUENCE {               
                hwCBQoSGlobalMultiPolicyStatClassifierIndex
                    Integer32,
                hwCBQoSGlobalMultiPolicyStatClassifierName
                    OCTET STRING,				
                hwCBQoSGlobalMultiPolicyStatClassifierMatchedPackets
                    Counter64,
                hwCBQoSGlobalMultiPolicyStatClassifierMatchedBytes
                    Counter64,
                hwCBQoSGlobalMultiPolicyStatClassifierMatchedPassPackets
                    Counter64,
                hwCBQoSGlobalMultiPolicyStatClassifierMatchedPassBytes
                    Counter64,
                hwCBQoSGlobalMultiPolicyStatClassifierMatchedDropPackets
                    Counter64,
                hwCBQoSGlobalMultiPolicyStatClassifierMatchedDropBytes
                    Counter64
                    }
			            
        hwCBQoSGlobalMultiPolicyStatClassifierIndex OBJECT-TYPE
            SYNTAX Integer32
            MAX-ACCESS read-only
            STATUS current
            DESCRIPTION
                "The value of this object identifies the classifier index."
            ::= { hwCBQoSGlobalMultiPolicyStatisticsClassifierEntry 1 }    
		
        hwCBQoSGlobalMultiPolicyStatClassifierName OBJECT-TYPE
            SYNTAX OCTET STRING (SIZE (1..31))
            MAX-ACCESS read-only
            STATUS current
            DESCRIPTION
                "Name of classifier."
            ::= { hwCBQoSGlobalMultiPolicyStatisticsClassifierEntry 2 }
        
        hwCBQoSGlobalMultiPolicyStatClassifierMatchedPackets OBJECT-TYPE
            SYNTAX Counter64
            MAX-ACCESS read-only
            STATUS current
            DESCRIPTION
                "Number of matched packets."
            ::= { hwCBQoSGlobalMultiPolicyStatisticsClassifierEntry 3 }
        
        hwCBQoSGlobalMultiPolicyStatClassifierMatchedBytes OBJECT-TYPE
            SYNTAX Counter64
            MAX-ACCESS read-only
            STATUS current
            DESCRIPTION
                "Number of matched bytes."
            ::= { hwCBQoSGlobalMultiPolicyStatisticsClassifierEntry 4 }
  
        hwCBQoSGlobalMultiPolicyStatClassifierMatchedPassPackets OBJECT-TYPE
            SYNTAX Counter64
            MAX-ACCESS read-only
            STATUS current
            DESCRIPTION
                "Number of packets that match the traffic classifier and pass through"
            ::= { hwCBQoSGlobalMultiPolicyStatisticsClassifierEntry 5 }
            

        hwCBQoSGlobalMultiPolicyStatClassifierMatchedPassBytes OBJECT-TYPE
            SYNTAX Counter64
            MAX-ACCESS read-only
            STATUS current
            DESCRIPTION
                "Number of bytes that match the traffic classifier and pass through"
            ::= { hwCBQoSGlobalMultiPolicyStatisticsClassifierEntry 6 }
            

        hwCBQoSGlobalMultiPolicyStatClassifierMatchedDropPackets OBJECT-TYPE
            SYNTAX Counter64
            MAX-ACCESS read-only
            STATUS current
            DESCRIPTION
                "Number of packets that match the traffic classifier and discard"
            ::= { hwCBQoSGlobalMultiPolicyStatisticsClassifierEntry 7 }
            
 
        hwCBQoSGlobalMultiPolicyStatClassifierMatchedDropBytes OBJECT-TYPE
            SYNTAX Counter64
            MAX-ACCESS read-only
            STATUS current
            DESCRIPTION
                "Number of bytes that match the traffic classifier and discard"
            ::= { hwCBQoSGlobalMultiPolicyStatisticsClassifierEntry 8 }
			
-- hwCBQoSGeneral

    hwCBQoSGeneral OBJECT IDENTIFIER ::= { hwCBQoSObjects 6 }    
    
    hwCBQoSFrameId OBJECT-TYPE   
        SYNTAX Integer32 
        MAX-ACCESS read-only
        STATUS current
        DESCRIPTION
            "The ID of the frame."
        ::= { hwCBQoSGeneral 1 }
        
    hwCBQoSSlotId OBJECT-TYPE   
        SYNTAX Integer32
        MAX-ACCESS read-only
        STATUS current
        DESCRIPTION
            "The ID of the slot that the interface is located"
        ::= { hwCBQoSGeneral 2 }   
        
    hwCBQoSPortId OBJECT-TYPE   
        SYNTAX Integer32
        MAX-ACCESS read-only
        STATUS current
        DESCRIPTION
            "The ID of the port"
        ::= { hwCBQoSGeneral 3 }     
    
    hwCBQoSTrapIfName OBJECT-TYPE   
        SYNTAX OCTET STRING (SIZE (1..31)) 
        MAX-ACCESS read-only
        STATUS current
        DESCRIPTION
            "Interface Name."
        ::= { hwCBQoSGeneral 4 }   
        
    hwCBQoSTrapType OBJECT-TYPE   
        SYNTAX INTEGER 
        { 
            cir(1),
            pir(2)
        }
        MAX-ACCESS read-only
        STATUS current
        DESCRIPTION
            "The type of the CAR alarm."
        ::= { hwCBQoSGeneral 5 }   
        
    
    hwCBQoSTrapAction OBJECT-TYPE   
        SYNTAX INTEGER 
        { 
            remark(1),
            drop(2)
        }
        MAX-ACCESS read-only
        STATUS current
        DESCRIPTION
            "The action that will be taken when trap is happened."
        ::= { hwCBQoSGeneral 6 }           
        
    hwCBQoSTrapPolicyName OBJECT-TYPE   
        SYNTAX OCTET STRING (SIZE (1..64)) 
        MAX-ACCESS read-only
        STATUS current
        DESCRIPTION
            "Policy Name."
        ::= { hwCBQoSGeneral 7 }
        
    hwCBQoSTrapVlanId OBJECT-TYPE 
        SYNTAX Integer32 
        MAX-ACCESS read-only
        STATUS current
        DESCRIPTION
            "The vlan that the policy applied."
        ::= { hwCBQoSGeneral 8 }      
        
        
    hwCBQoSTrapEgressIfName OBJECT-TYPE 
        SYNTAX OCTET STRING (SIZE (1..31)) 
        MAX-ACCESS read-only
        STATUS current
        DESCRIPTION
            "The name of Egress Interface."
        ::= { hwCBQoSGeneral 9 } 
        
    hwCBQoSTrapDiscardPackets OBJECT-TYPE 
        SYNTAX Counter64 
        MAX-ACCESS read-only
        STATUS current
        DESCRIPTION
            "The number of discarded packets."
        ::= { hwCBQoSGeneral 10 }               
        
        
-- begin by z00198832        
        -- hwCBQoSQueryObjects
        hwCBQoSQueryObjects OBJECT IDENTIFIER ::= { hwCBQoSObjects 7 }

        
--  hwCBQoSClassifierIndexQueryTable
        hwCBQoSClassifierIndexQueryTable OBJECT-TYPE
            SYNTAX SEQUENCE OF HwCBQoSClassifierIndexQueryEntry
            MAX-ACCESS not-accessible
            STATUS current
            DESCRIPTION
                "A table of QoS ClassifierIndexQuery."
            ::= { hwCBQoSQueryObjects 1 }

        
        hwCBQoSClassifierIndexQueryEntry OBJECT-TYPE
            SYNTAX HwCBQoSClassifierIndexQueryEntry
            MAX-ACCESS not-accessible
            STATUS current
            DESCRIPTION
                "QoS Classifier Query Entry."
            INDEX { hwCBQoSQueryPolicyName, hwCBQoSQueryClassifierName }
            ::= { hwCBQoSClassifierIndexQueryTable 1 }

        
        HwCBQoSClassifierIndexQueryEntry ::=
            SEQUENCE { 
                hwCBQoSQueryPolicyName
                    OCTET STRING,
                hwCBQoSQueryClassifierName
                    OCTET STRING,
                hwCBQoSQueryClassifierIndex
                    Integer32   
             }

        hwCBQoSQueryPolicyName OBJECT-TYPE
            SYNTAX OCTET STRING (SIZE (1..64))
            MAX-ACCESS read-only
            STATUS current
            DESCRIPTION
                "The name of QoS policy"
            ::= { hwCBQoSClassifierIndexQueryEntry 1 }

        
        hwCBQoSQueryClassifierName OBJECT-TYPE
            SYNTAX OCTET STRING (SIZE (1..64))
            MAX-ACCESS read-only
            STATUS current
            DESCRIPTION
                "The name of qos classfier"
            ::= { hwCBQoSClassifierIndexQueryEntry 2 }

        
        hwCBQoSQueryClassifierIndex OBJECT-TYPE
            SYNTAX Integer32
            MAX-ACCESS read-create
            STATUS current
            DESCRIPTION
                "This value of qos classifier index."
            ::= { hwCBQoSClassifierIndexQueryEntry 3 }        
-- end by z00198832   
                     
        
    hwCBQoSNotifications OBJECT IDENTIFIER ::= { hwCBQoSMIB 2 }   
         
        hwCBQoSGtsDiscardThresholdTrap NOTIFICATION-TYPE
            OBJECTS {hwCBQoSFrameId, hwCBQoSSlotId, hwCBQoSPortId, hwCBQoSClassifierName, hwCBQoSBehaviorName, hwCBQoSTrapIfName, hwCBQoSTrapPolicyName, hwCBQoSTrapVlanId, hwCBQoSTrapEgressIfName, hwCBQoSTrapDiscardPackets
                 }
            STATUS current
            DESCRIPTION 
                "The SNMP trap is generated when the number of packages 
                that Gts discard is larger than the configured threshold."
            ::= { hwCBQoSNotifications 1 }
        
        hwCBQoSCarOverSpeedThresholdTrap NOTIFICATION-TYPE
            OBJECTS {hwCBQoSFrameId, hwCBQoSSlotId, hwCBQoSPortId, hwCBQoSClassifierName, hwCBQoSBehaviorName, hwCBQoSTrapIfName, hwCBQoSTrapPolicyName, hwCBQoSTrapVlanId, hwCBQoSTrapType, hwCBQoSTrapAction, hwCBQoSTrapDiscardPackets
                 }
            STATUS current
            DESCRIPTION 
                "The SNMP trap is generated when the speed of cir or pir 
                exceeds the configured threshold."
            ::= { hwCBQoSNotifications 2 }
            
        --beg: mod by j00126783 for policy-alarm                                                                                                                                            
        -- 1.3.6.1.4.1.2011.5.25.32.1.2.3
        hwCBQoSRuleNotSupportAlarm NOTIFICATION-TYPE
            OBJECTS { hwCBQoSRuleDirection, hwCBQoSRuleSlotID, hwCBQoSRuleInfo }
            STATUS current
            DESCRIPTION 
                "The SNMP trap is generated when the rule is not supported."
            ::= { hwCBQoSNotifications 3 }

        
--  1.3.6.1.4.1.2011.5.25.32.1.2.4
        -- 1.3.6.1.4.1.2011.5.25.32.1.2.4
        hwCBQoSActionNotSupportAlarm NOTIFICATION-TYPE
            OBJECTS { hwCBQoSActionDirection, hwCBQoSActionSlotID, hwCBQoSActionInfo }
            STATUS current
            DESCRIPTION 
                "The SNMP trap is generated when the action is not supported."
            ::= { hwCBQoSNotifications 4 }
			
        hwCBQoSGlobalAclNotSupportAlarm NOTIFICATION-TYPE
            OBJECTS { hwCBQoSGlobalAclDirection, hwCBQoSGlobalAclSlotID }
            STATUS current
            DESCRIPTION 
                "The SNMP trap is generated when the Global ACL is not support the ACL."
            ::= { hwCBQoSNotifications 5 }
       --end: mod by j00126783 for policy-alarm
 
       --Beg: mod by l00200458 on 20160528                        
       -- 1.3.6.1.4.1.2011.5.25.32.1.2.6
       hwCBQoSUpdateUserQueueResourceNotEnoughAlarm NOTIFICATION-TYPE
            OBJECTS { hwCBQoSUpdateUserQueueBehaviorName, hwCBQoSUpdateUserQueueSlotID, hwCBQoSUpdateUserQueueCir, hwCBQoSUpdateUserQueuePir }
            STATUS current
            DESCRIPTION 
                "The SNMP trap is generated when the action user-queue update failed."
            ::= { hwCBQoSNotifications 6 }
       -- 1.3.6.1.4.1.2011.5.25.32.1.2.7
       hwCBQoSSetUserQueueResourceNotEnoughAlarm NOTIFICATION-TYPE
            OBJECTS { hwCBQoSSetUserQueueBehaviorName, hwCBQoSSetUserQueueSlotID }
            STATUS current
            DESCRIPTION 
                "The SNMP trap is generated when the action user-queue config failed."
            ::= { hwCBQoSNotifications 7 }
       --End: mod by l00200458 on 20160528                        
        hwCBQoSConformance OBJECT IDENTIFIER ::= { hwCBQoSMIB 3 }
        hwCBQoSCompliances OBJECT IDENTIFIER ::= { hwCBQoSConformance 1 }
   
--  compliance statements
-- this module
        hwCBQoSCompliance MODULE-COMPLIANCE
            STATUS current
            DESCRIPTION 
                "The compliance statement for entities that implement
                class-based QoS on a router."
            MODULE -- this module
                MANDATORY-GROUPS { hwCBQoSClassifierGroup, hwCBQoSBehaviorGroup, hwCBQoSCarGroup, hwCBQoSGtsGroup, hwCBQoSRemarkGroup, 
                    hwCBQoSQueueGroup, hwCBQoSWredGroup, hwCBQoSNatGroup, hwCBQoSFirewallGroup, 
                    hwCBQoSSamplingGroup, hwCBQoSPolicyGroup, hwCBQoSIfApplyPolicyGroup, hwCBQoSAtmPvcApplyPolicyGroup, hwCBQoSIfVlanApplyPolicyGroup, 
                    hwCBQoSFrClassApplyPolicyGroup, hwCBQoSFrPvcApplyPolicyGroup, hwCBQoSIfCbqRunInfoGroup, hwCBQoSIfClassMatchRunInfoGroup, hwCBQoSIfCarRunInfoGroup, 
                    hwCBQoSIfGtsRunInfoGroup, hwCBQoSIfRemarkRunInfoGroup, hwCBQoSIfQueueRunInfoGroup, hwCBQoSIfWredRunInfoGroup, hwCBQoSAtmPvcCbqRunInfoGroup, 
                    hwCBQoSAtmPvcClassMatchRunInfoGroup, hwCBQoSAtmPvcCarRunInfoGroup, hwCBQoSAtmPvcGtsRunInfoGroup, hwCBQoSAtmPvcRemarkRunInfoGroup, hwCBQoSAtmPvcQueueRunInfoGroup, 
                    hwCBQoSAtmPvcWredRunInfoGroup, hwCBQoSFrPvcCbqRunInfoGroup, hwCBQoSFrPvcClassMatchRunInfoGroup, hwCBQoSFrPvcCarRunInfoGroup, hwCBQoSFrPvcGtsRunInfoGroup, 
                    hwCBQoSFrPvcRemarkRunInfoGroup, hwCBQoSFrPvcQueueRunInfoGroup, hwCBQoSFrPvcWredRunInfoGroup, hwCBQoSIfVlanClassMatchRunInfoGroup, hwCBQoSLrGroup, 
                    hwCBQoSNestPolicyGroup, hwCBQoSIfLrRunInfoGroup, hwCBQoSAtmPvcLrRunInfoGroup, hwCBQoSFrPvcLrRunInfoGroup, hwCBQoSCarStatisticsGroup, 
                    hwCBQoSPolicyStatisticsGroup,  hwCBQoSRuleNotSupportAlarmGroup, hwCBQoSActionNotSupportAlarmGroup, hwCBQoSGlobalAclNotSupportAlarmGroup, 
                    hwCBQoSUpdateUserQueueResourceNotEnoughAlarmGroup, hwCBQoSSetUserQueueResourceNotEnoughAlarmGroup}
            ::= { hwCBQoSCompliances 1 }

        
        hwCBQoSGroups OBJECT IDENTIFIER ::= { hwCBQoSConformance 2 }

        
--  units of conformance
        hwCBQoSClassifierGroup OBJECT-GROUP
            OBJECTS { hwCBQoSClassifierIndexNext, hwCBQoSClassifierIndex, hwCBQoSClassifierName, hwCBQoSClassifierRuleCount, hwCBQoSClassifierOperator, 
                hwCBQoSClassifierLayer, hwCBQoSClassifierRowStatus, hwCBQoSMatchRuleIndex, hwCBQoSMatchRuleIfNot, hwCBQoSMatchRuleType, 
                hwCBQoSMatchRuleStringValue, hwCBQoSMatchMacMask, hwCBQoSMatchRuleIntValue1, hwCBQoSMatchRuleIntValue2, hwCBQoSMatchRuleRowStatus,
                hwCBQoSMatchVlanEndId, hwCBQoSMatchInnerSrcIp, hwCBQoSMatchInnerSrcIpMask, hwCBQoSMatchInnerDstIp, hwCBQoSMatchInnerDstIpMask,
                hwCBQoSMatchInnerSrcPort,  hwCBQoSMatchInnerDstPort, hwCBQoSMatchInnerProtocol, hwCBQoSMatchVxlanVni
                 }
            STATUS current
            DESCRIPTION 
                "Required objects to provide CB QoS objects configuration
                information. hwCBQoSClassifierLayer is optional."
            ::= { hwCBQoSGroups 1 }

        
        hwCBQoSBehaviorGroup OBJECT-GROUP
            OBJECTS { hwCBQoSBehaviorIndexNext, hwCBQoSBehaviorIndex, hwCBQoSBehaviorName, hwCBQoSBehaviorRowStatus }
            STATUS current
            DESCRIPTION 
                "Required objects to provide CB QoS objects configuration
                information. One of
                hwCBQoSCarGroup,
                hwCBQoSGtsGroup,
                hwCBQoSRemarkGroup,
                hwCBQoSQueueGroup,
                hwCBQoSWredGroup,
                
                hwCBQoSNatGroup,
                hwCBQoSFirewallGroup,
                hwCBQoSSamplingGroup should be required."
            ::= { hwCBQoSGroups 2 }

        
        hwCBQoSCarGroup OBJECT-GROUP
            OBJECTS { hwCBQoSCarCir, hwCBQoSCarCbs, hwCBQoSCarEbs, hwCBQoSCarGreenAction, hwCBQoSCarGreenRemarkValue, 
                hwCBQoSCarRedAction, hwCBQoSCarRedRemarkValue, hwCBQoSCarPir, hwCBQoSCarPbs, hwCBQoSCarYellowAction, 
                hwCBQoSCarYellowRemarkValue, hwCBQoSCarRowStatus,hwCBQosCarAggregation }
            STATUS current
            DESCRIPTION 
                "This is a optional group of information."
            ::= { hwCBQoSGroups 3 }

        
        hwCBQoSGtsGroup OBJECT-GROUP
            OBJECTS { hwCBQoSGtsCir, hwCBQoSGtsCbs, hwCBQoSGtsPir, hwCBQoSGtsEbs, hwCBQoSGtsQueueLength, 
                hwCBQoSGtsRowStatus }
            STATUS current
            DESCRIPTION 
                "This is a optional group of information."
            ::= { hwCBQoSGroups 4 }

        
        hwCBQoSRemarkGroup OBJECT-GROUP
            OBJECTS { hwCBQoSRemarkType, hwCBQoSRemarkValue, hwCBQoSRemarkRowStatus, hwCBQoSRemarkStringValue }
            STATUS current
            DESCRIPTION 
                "This is a optional group of information."
            ::= { hwCBQoSGroups 5 }

        
        hwCBQoSQueueGroup OBJECT-GROUP
            OBJECTS { hwCBQoSQueueType, hwCBQoSQueueDropType, hwCBQoSQueueLength, hwCBQoSQueueBandwidthUnit, hwCBQoSQueueBandwidthValue, 
                hwCBQoSQueueCbs, hwCBQoSQueueQueueNumber, hwCBQoSQueueRowStatus, hwCBQoSQueueCbsRatio }
            STATUS current
            DESCRIPTION 
                "This is a optional group of information."
            ::= { hwCBQoSGroups 6 }

        
        hwCBQoSWredGroup OBJECT-GROUP
            OBJECTS { hwCBQoSWredType, hwCBQoSWredWeightConst, hwCBQoSWredClassValue, hwCBQoSWredClassLowLimit, hwCBQoSWredClassHighLimit, 
                hwCBQoSWredClassDiscardProb }
            STATUS current
            DESCRIPTION 
                "This is a optional group of information."
            ::= { hwCBQoSGroups 7 }

        
        -- hwCBQoSPolicyRouteGroup OBJECT-GROUP    
        --    OBJECTS {}
        --    STATUS current
        --    DESCRIPTION 
        --        "This is a optional group of information."
        --    ::= { hwCBQoSGroups 8 }

        
        hwCBQoSNatGroup OBJECT-GROUP
            OBJECTS { hwCBQoSNatServiceClass, hwCBQoSNatRowStatus, hwCBQoSNatNoPat }
            STATUS current
            DESCRIPTION 
                "This is a optional group of information."
            ::= { hwCBQoSGroups 9 }

        
        hwCBQoSFirewallGroup OBJECT-GROUP
            OBJECTS { hwCBQoSFirewallAction, hwCBQoSFirewallRowStatus }
            STATUS current
            DESCRIPTION 
                "This is a optional group of information."
            ::= { hwCBQoSGroups 10 }

        
        hwCBQoSSamplingGroup OBJECT-GROUP
            OBJECTS { hwCBQoSSamplingNum, hwCBQoSSamplingRowStatus, hwCBQoSIfSamplingType }
            STATUS current
            DESCRIPTION 
                "This is a optional group of information."
            ::= { hwCBQoSGroups 11 }    
            
        hwCBQoSEgressGtsGroup OBJECT-GROUP
            OBJECTS {
            hwCBQoSEgressGtsCir,
            hwCBQoSEgressGtsPir,
            hwCBQoSEgressGtsRowStatus   
            }
            STATUS      current
            DESCRIPTION
            "This is a optional group of information."
            ::= { hwCBQoSGroups 12 }  
                 
        hwCBQoSServiceClassGroup  OBJECT-GROUP    
            OBJECTS {
            hwCBQoSServiceClassQueueId,
            hwCBQoSServiceClassColor,
            hwCBQoSServiceClassRowStatus,
            hwCBQoSServiceClassNoremarkflag
            }
            STATUS      current
            DESCRIPTION
            "This is a optional group of information."
            ::= { hwCBQoSGroups 13 }     

        
        hwCBQoSPolicyGroup OBJECT-GROUP
            OBJECTS { hwCBQoSPolicyIndexNext, hwCBQoSPolicyIndex, hwCBQoSPolicyName, hwCBQoSPolicyClassCount, hwCBQoSPolicyRowStatus, 
                hwCBQoSPolicyClassIndex, hwCBQoSPolicyClassClassifierIndex, hwCBQoSPolicyClassClassifierName, hwCBQoSPolicyClassBehaviorIndex, hwCBQoSPolicyClassBehaviorName, 
                hwCBQoSPolicyConfigMode, hwCBQoSPolicyClassPrecedence, hwCBQoSPolicyClassRowStatus, hwCBQoSPolicyShareFlag, hwCBQoSPolicyStatisticsFlag
                 }
            STATUS current
            DESCRIPTION 
                "Required objects to provide CB QoS objects configuration
                information. hwCBQoSPolicyConfigMode, hwCBQoSPolicyClassPrecedence
                is optional."
        ::= { hwCBQoSGroups 14 }

        
        hwCBQoSIfApplyPolicyGroup OBJECT-GROUP
            OBJECTS { hwCBQoSIfApplyPolicyIfIndex, hwCBQoSIfApplyPolicyDirection, hwCBQoSIfApplyPolicyName, hwCBQoSIfApplyPolicyRowStatus, hwCBQoSIfApplyPolicyLinkLayer }
            STATUS current
            DESCRIPTION 
                "Required objects to provide CB QoS objects configuration
                information."
        ::= { hwCBQoSGroups 15 }

        
        hwCBQoSAtmPvcApplyPolicyGroup OBJECT-GROUP
            OBJECTS { hwCBQoSAtmPvcApplyPolicyIfIndex, hwCBQoSAtmPvcApplyPolicyVPI, hwCBQoSAtmPvcApplyPolicyVCI, hwCBQoSAtmPvcApplyPolicyDirection, hwCBQoSAtmPvcApplyPolicyName, 
                hwCBQoSAtmPvcApplyPolicyRowStatus }
            STATUS current
            DESCRIPTION 
                "This is a optional group of information."
        ::= { hwCBQoSGroups 16 }

        
        hwCBQoSIfVlanApplyPolicyGroup OBJECT-GROUP
            OBJECTS { hwCBQoSIfVlanApplyPolicyIfIndex, hwCBQoSIfVlanApplyPolicyDirection, hwCBQoSIfVlanApplyPolicyVlanid1, hwCBQoSIfVlanApplyPolicyVlanid2, hwCBQoSIfVlanApplyPolicyName, hwCBQoSIfVlanApplyPolicyRowStatus, hwCBQoSIfVlanApplyPolicyLinkLayer }
            STATUS current
            DESCRIPTION 
                "This is a optional group of information"
        ::= { hwCBQoSGroups 17 }

        
        hwCBQoSFrClassApplyPolicyGroup OBJECT-GROUP
            OBJECTS { hwCBQoSFrClassApplyPolicyFrClassName, hwCBQoSFrClassApplyPolicyDirection, hwCBQoSFrClassApplyPolicyName, hwCBQoSFrClassApplyPolicyRowStatus }
            STATUS current
            DESCRIPTION 
                "This is a optional group of information."
        ::= { hwCBQoSGroups 18 }

        
        hwCBQoSFrPvcApplyPolicyGroup OBJECT-GROUP
            OBJECTS { hwCBQoSFrPvcApplyPolicyIfIndex, hwCBQoSFrPvcApplyPolicyDlciNum, hwCBQoSFrPvcApplyPolicyDirection, hwCBQoSFrPvcApplyPolicyName }
            STATUS current
            DESCRIPTION 
                "This is a optional group of information."
        ::= { hwCBQoSGroups 19 }

        
        hwCBQoSIfCbqRunInfoGroup OBJECT-GROUP
            OBJECTS { hwCBQoSIfCbqQueueSize, hwCBQoSIfCbqDiscard, hwCBQoSIfCbqEfQueueSize, hwCBQoSIfCbqAfQueueSize, hwCBQoSIfCbqBeQueueSize, 
                hwCBQoSIfCbqBeActiveQueueNum, hwCBQoSIfCbqBeMaxActiveQueueNum, hwCBQoSIfCbqBeTotalQueueNum, hwCBQoSIfCbqAfAllocatedQueueNum }
            STATUS current
            DESCRIPTION 
                "This is a optional group of information."
        ::= { hwCBQoSGroups 20 }

        
        hwCBQoSIfClassMatchRunInfoGroup OBJECT-GROUP
            OBJECTS { hwCBQoSIfClassMatchedPackets, hwCBQoSIfClassMatchedBytes, hwCBQoSIfClassAverageRate }
            STATUS current
            DESCRIPTION 
                "Required objects to provide CB QoS objects configuration
                information."
        ::= { hwCBQoSGroups 21 }

        
        hwCBQoSIfCarRunInfoGroup OBJECT-GROUP     
            OBJECTS {
                hwCBQoSIfCarGreenPassedPackets,
                hwCBQoSIfCarGreenPassedBytes,
                hwCBQoSIfCarGreenRemarkedPackets,
                hwCBQoSIfCarGreenRemarkedBytes,
                hwCBQoSIfCarGreenDiscardedPackets,
                hwCBQoSIfCarGreenDiscardedBytes,
                hwCBQoSIfCarYellowPassedPackets,
                hwCBQoSIfCarYellowPassedBytes,
                hwCBQoSIfCarYellowRemarkedPackets,
                hwCBQoSIfCarYellowRemarkedBytes,
                hwCBQoSIfCarYellowDiscardedPackets,
                hwCBQoSIfCarYellowDiscardedBytes,
                hwCBQoSIfCarRedPassedPackets,
                hwCBQoSIfCarRedPassedBytes,
                hwCBQoSIfCarRedRemarkedPackets,
                hwCBQoSIfCarRedRemarkedBytes,
                hwCBQoSIfCarRedDiscardedPackets,
                hwCBQoSIfCarRedDiscardedBytes}
            STATUS current
            DESCRIPTION 
                "This is a optional group of information."
        ::= { hwCBQoSGroups 22 } 

        
        hwCBQoSIfGtsRunInfoGroup OBJECT-GROUP
            OBJECTS { hwCBQoSIfGtsPassedPackets, hwCBQoSIfGtsPassedBytes, hwCBQoSIfGtsDiscardedPackets, hwCBQoSIfGtsDiscardedBytes, hwCBQoSIfGtsDelayedPackets, 
                hwCBQoSIfGtsDelayedBytes, hwCBQoSIfGtsQueueSize }
            STATUS current
            DESCRIPTION 
                "This is a optional group of information."
        ::= { hwCBQoSGroups 23 } 

        
        hwCBQoSIfRemarkRunInfoGroup OBJECT-GROUP
            OBJECTS { hwCBQoSIfRemarkedPackets }
            STATUS current
            DESCRIPTION 
                "This is a optional group of information."
        ::= { hwCBQoSGroups 24 } 

        
        hwCBQoSIfQueueRunInfoGroup OBJECT-GROUP
            OBJECTS { hwCBQoSIfQueueMatchedPackets, hwCBQoSIfQueueMatchedBytes, hwCBQoSIfQueueEnqueuedPackets, hwCBQoSIfQueueEnqueuedBytes, hwCBQoSIfQueueDiscardedPackets, 
                hwCBQoSIfQueueDiscardedBytes }
            STATUS current
            DESCRIPTION 
                "This is a optional group of information."
        ::= { hwCBQoSGroups 25 } 

        
        hwCBQoSIfWredRunInfoGroup OBJECT-GROUP
            OBJECTS { hwCBQoSIfWredRandomDiscardedPackets, hwCBQoSIfWredTailDiscardedPackets }
            STATUS current
            DESCRIPTION 
                "This is a optional group of information."
        ::= { hwCBQoSGroups 26 }       

        
        hwCBQoSAtmPvcCbqRunInfoGroup OBJECT-GROUP
            OBJECTS { hwCBQoSAtmPvcCbqQueueSize, hwCBQoSAtmPvcCbqDiscard, hwCBQoSAtmPvcCbqEfQueueSize, hwCBQoSAtmPvcCbqAfQueueSize, hwCBQoSAtmPvcCbqBeQueueSize, 
                hwCBQoSAtmPvcCbqBeActiveQueueNum, hwCBQoSAtmPvcCbqBeMaxActiveQueueNum, hwCBQoSAtmPvcCbqBeTotalQueueNum, hwCBQoSAtmPvcCbqAfAllocatedQueueNum }
            STATUS current
            DESCRIPTION 
                "This is a optional group of information."
        ::= { hwCBQoSGroups 27 }

        
        hwCBQoSAtmPvcClassMatchRunInfoGroup OBJECT-GROUP
            OBJECTS { hwCBQoSAtmPvcClassMatchPackets, hwCBQoSAtmPvcClassMatchBytes, hwCBQoSAtmPvcClassAverageRate }
            STATUS current
            DESCRIPTION 
                "This is a optional group of information."
        ::= { hwCBQoSGroups 28 }

        
        hwCBQoSAtmPvcCarRunInfoGroup OBJECT-GROUP
            OBJECTS { hwCBQoSAtmPvcCarConformPackets, hwCBQoSAtmPvcCarConformBytes, hwCBQoSAtmPvcCarExceedPackets, hwCBQoSAtmPvcCarExceedBytes }
            STATUS current
            DESCRIPTION 
                "This is a optional group of information."
        ::= { hwCBQoSGroups 29 }        

        
        hwCBQoSAtmPvcGtsRunInfoGroup OBJECT-GROUP
            OBJECTS { hwCBQoSAtmPvcGtsPassedPackets, hwCBQoSAtmPvcGtsPassedBytes, hwCBQoSAtmPvcGtsDiscardedPackets, hwCBQoSAtmPvcGtsDiscardedBytes, hwCBQoSAtmPvcGtsDelayedPackets, 
                hwCBQoSAtmPvcGtsDelayedBytes, hwCBQoSAtmPvcGtsQueueSize }
            STATUS current
            DESCRIPTION 
                "This is a optional group of information."
        ::= { hwCBQoSGroups 30 }        

        
        hwCBQoSAtmPvcRemarkRunInfoGroup OBJECT-GROUP
            OBJECTS { hwCBQoSAtmPvcRemarkedPackets }
            STATUS current
            DESCRIPTION 
                "This is a optional group of information."
        ::= { hwCBQoSGroups 31 }

        
        hwCBQoSAtmPvcQueueRunInfoGroup OBJECT-GROUP
            OBJECTS { hwCBQoSAtmPvcQueueMatchedPackets, hwCBQoSAtmPvcQueueMatchedBytes, hwCBQoSAtmPvcQueueEnqueuedPackets, hwCBQoSAtmPvcQueueEnqueuedBytes, hwCBQoSAtmPvcQueueDiscardedPackets, 
                hwCBQoSAtmPvcQueueDiscardedBytes }
            STATUS current
            DESCRIPTION 
                "This is a optional group of information."
        ::= { hwCBQoSGroups 32 }

        
        hwCBQoSAtmPvcWredRunInfoGroup OBJECT-GROUP
            OBJECTS { hwCBQoSAtmPvcWredRandomDiscardedPackets, hwCBQoSAtmPvcWredTailDiscardedPackets }
            STATUS current
            DESCRIPTION 
                "RThis is a optional group of information."
        ::= { hwCBQoSGroups 33 }

        
        hwCBQoSFrPvcCbqRunInfoGroup OBJECT-GROUP
            OBJECTS { hwCBQoSFrPvcCbqQueueSize, hwCBQoSFrPvcCbqDiscard, hwCBQoSFrPvcCbqEfQueueSize, hwCBQoSFrPvcCbqAfQueueSize, hwCBQoSFrPvcCbqBeQueueSize, 
                hwCBQoSFrPvcCbqBeActiveQueueNum, hwCBQoSFrPvcCbqBeMaxActiveQueueNum, hwCBQoSFrPvcCbqBeTotalQueueNum, hwCBQoSFrPvcCbqAfAllocatedQueueNum }
            STATUS current
            DESCRIPTION 
                "This is a optional group of information."
        ::= { hwCBQoSGroups 34 }

        
        hwCBQoSFrPvcClassMatchRunInfoGroup OBJECT-GROUP
            OBJECTS { hwCBQoSFrPvcClassMatchedPackets, hwCBQoSFrPvcClassMatchedBytes, hwCBQoSFrPvcClassAverageRate }
            STATUS current
            DESCRIPTION 
                "This is a optional group of information."
        ::= { hwCBQoSGroups 35 }

        
        hwCBQoSFrPvcCarRunInfoGroup OBJECT-GROUP
            OBJECTS { hwCBQoSFrPvcCarConformPackets, hwCBQoSFrPvcCarConformBytes, hwCBQoSFrPvcCarExceedPackets, hwCBQoSFrPvcCarExceedBytes }
            STATUS current
            DESCRIPTION 
                "This is a optional group of information."
        ::= { hwCBQoSGroups 36 }

        
        hwCBQoSFrPvcGtsRunInfoGroup OBJECT-GROUP
            OBJECTS { hwCBQoSFrPvcGtsPassedPackets, hwCBQoSFrPvcGtsPassedBytes, hwCBQoSFrPvcGtsDiscardedPackets, hwCBQoSFrPvcGtsDiscardedBytes, hwCBQoSFrPvcGtsDelayedPackets, 
                hwCBQoSFrPvcGtsDelayedBytes, hwCBQoSFrPvcGtsQueueSize }
            STATUS current
            DESCRIPTION 
                "This is a optional group of information."
        ::= { hwCBQoSGroups 37 }

        
        hwCBQoSFrPvcRemarkRunInfoGroup OBJECT-GROUP
            OBJECTS { hwCBQoSFrPvcRemarkedPackets }
            STATUS current
            DESCRIPTION 
                "This is a optional group of information."
        ::= { hwCBQoSGroups 38 }

        
        hwCBQoSFrPvcQueueRunInfoGroup OBJECT-GROUP
            OBJECTS { hwCBQoSFrPvcQueueMatchedPackets, hwCBQoSFrPvcQueueMatchedBytes, hwCBQoSFrPvcQueueEnqueuedPackets, hwCBQoSFrPvcQueueEnqueuedBytes, hwCBQoSFrPvcQueueDiscardedPackets, 
                hwCBQoSFrPvcQueueDiscardedBytes }
            STATUS current
            DESCRIPTION 
                "This is a optional group of information."
        ::= { hwCBQoSGroups 39 }

        
        hwCBQoSFrPvcWredRunInfoGroup OBJECT-GROUP
            OBJECTS { hwCBQoSFrPvcWredRandomDiscardedPackets, hwCBQoSFrPvcWredTailDiscardedPackets }
            STATUS current
            DESCRIPTION 
                "This is a optional group of information."
        ::= { hwCBQoSGroups 40 }

        
        hwCBQoSIfVlanClassMatchRunInfoGroup OBJECT-GROUP
            OBJECTS { hwCBQoSIfVlanClassMatchedPackets }
            STATUS current
            DESCRIPTION 
                "This is a optional group of information."
        ::= { hwCBQoSGroups 41 } 

        
        hwCBQoSLrGroup OBJECT-GROUP
            OBJECTS { hwCBQoSLrUnit, hwCBQoSLrCir, hwCBQoSLrCbs, hwCBQoSLrEbs, hwCBQoSLrRowStatus
                 }
            STATUS current
            DESCRIPTION 
                "This is a optional group of information."
            ::= { hwCBQoSGroups 42 }

        
        hwCBQoSNestPolicyGroup OBJECT-GROUP
            OBJECTS { hwCBQoSNestPolicyName, hwCBQoSNestPolicyRowStatus }
            STATUS current
            DESCRIPTION 
                "This is a optional group of information."
        ::= { hwCBQoSGroups 43 }

        
        hwCBQoSIfLrRunInfoGroup OBJECT-GROUP
            OBJECTS { hwCBQoSIfLrPassedPackets, hwCBQoSIfLrPassedBytes, hwCBQoSIfLrDiscardedPackets, hwCBQoSIfLrDiscardedBytes, hwCBQoSIfLrDelayedPackets, 
                hwCBQoSIfLrDelayedBytes }
            STATUS current
            DESCRIPTION 
                "This is a optional group of information."
        ::= { hwCBQoSGroups 44 }

        
        hwCBQoSAtmPvcLrRunInfoGroup OBJECT-GROUP
            OBJECTS { hwCBQoSAtmPvcLrPassedPackets, hwCBQoSAtmPvcLrPassedBytes, hwCBQoSAtmPvcLrDiscardedPackets, hwCBQoSAtmPvcLrDiscardedBytes, hwCBQoSAtmPvcLrDelayedPackets, 
                hwCBQoSAtmPvcLrDelayedBytes }
            STATUS current
            DESCRIPTION 
                "This is a optional group of information."
            ::= { hwCBQoSGroups 45 }

        
        hwCBQoSFrPvcLrRunInfoGroup OBJECT-GROUP
            OBJECTS { hwCBQoSFrPvcLrPassedPackets, hwCBQoSFrPvcLrPassedBytes, hwCBQoSFrPvcLrDiscardedPackets, hwCBQoSFrPvcLrDiscardedBytes, hwCBQoSFrPvcLrDelayedPackets, 
                hwCBQoSFrPvcLrDelayedBytes }
            STATUS current
            DESCRIPTION 
                "This is a optional group of information."
            ::= { hwCBQoSGroups 46 }

        
        hwCBQoSCarStatisticsGroup OBJECT-GROUP
            OBJECTS { hwCBQoSCarConformedPackets, hwCBQoSCarConformedBytes, hwCBQoSCarConformedPacketRate, hwCBQoSCarConformedByteRate, hwCBQoSCarExceededPackets, 
                hwCBQoSCarExceededBytes, hwCBQoSCarExceededPacketRate, hwCBQoSCarExceededByteRate, hwCBQoSCarOverflowPackets, hwCBQoSCarOverflowBytes, 
                hwCBQoSCarOverflowPacketRate, hwCBQoSCarOverflowByteRate, hwCBQoSCarPassedPackets, hwCBQoSCarPassedBytes, hwCBQoSCarDroppedPackets, 
                hwCBQoSCarDroppedBytes }
            STATUS current
            DESCRIPTION 
                "This is a optional group of information."
            ::= { hwCBQoSGroups 47}

        
        hwCBQoSPolicyStatisticsGroup OBJECT-GROUP
            OBJECTS { hwCBQoSPolicyMatchedPackets, hwCBQoSPolicyMatchedBytes, hwCBQoSPolicyUnmatchedPackets, hwCBQoSPolicyUnmatchedBytes, 
                hwCBQoSPolicyMatchedPassPackets, hwCBQoSPolicyMatchedPassBytes, hwCBQoSPolicyMatchedDropPackets, hwCBQoSPolicyMatchedDropBytes, hwCBQoSPolicyResetFlag }
            STATUS current
            DESCRIPTION 
                "This is a optional group of information."
            ::= { hwCBQoSGroups 48 }

        
        hwCBQoSRedirectGroup OBJECT-GROUP
            OBJECTS { hwCBQoSRedirectType, hwCBQoSRedirectIpAddress, hwCBQoSRedirectIfIndex, hwCBQoSRedirectVlanId, hwCBQoSRedirectCtrlType, 
                hwCBQoSRedirectRowStatus, hwCBQoSRedirectLSPDstIpAddress, hwCBQoSRedirectLSPSecondary }
            STATUS current
            DESCRIPTION 
                "This is a optional group of information."
            ::= { hwCBQoSGroups 49 }        
            
        hwCBQoSGeneralGroup OBJECT-GROUP  
            OBJECTS { hwCBQoSFrameId, hwCBQoSSlotId, hwCBQoSPortId, hwCBQoSTrapIfName, hwCBQoSTrapType,
                      hwCBQoSTrapAction, hwCBQoSTrapPolicyName, hwCBQoSTrapVlanId, hwCBQoSTrapEgressIfName,
                      hwCBQoSTrapDiscardPackets }
            STATUS current
            DESCRIPTION 
                "This is a optional group of information."
            ::= { hwCBQoSGroups 50 }    

        hwCBQoSNotificationsGroup NOTIFICATION-GROUP
        NOTIFICATIONS {hwCBQoSGtsDiscardThresholdTrap, hwCBQoSCarOverSpeedThresholdTrap, hwCBQoSRuleNotSupportAlarm, hwCBQoSActionNotSupportAlarm }
            STATUS current
            DESCRIPTION 
                "This is a optional group of information."
            ::= { hwCBQoSGroups 51 }           
            
        hwCBQoSPolicyShareModeGroup OBJECT-GROUP   
            OBJECTS {hwCBQoSPolicyShareModeFlag, hwCBQoSPolicyShareModeRowStatus}
            STATUS current
            DESCRIPTION 
                "This is a optional group of information."
            ::= { hwCBQoSGroups 52 }      

        hwCBQoSClassifierStatisticsGroup OBJECT-GROUP
            OBJECTS { hwCBQoSPolicyClassifierIndex, hwCBQoSClassifierMatchedPackets, hwCBQoSClassifierMatchedBytes, hwCBQoSClassifierMatchedPassPackets, hwCBQoSClassifierMatchedPassBytes, 
                hwCBQoSClassifierMatchedDropPackets, hwCBQoSClassifierMatchedDropBytes}
            STATUS current
            DESCRIPTION 
                "This is a optional group of information."
            ::= { hwCBQoSGroups 53 }   

            
    hwCBQoSPolicyStatisticsClassifierGroup OBJECT-GROUP
        OBJECTS { hwCBQoSPolicyStatClassifierMatchedPackets, hwCBQoSPolicyStatClassifierMatchedBytes, hwCBQoSPolicyStatClassifierUnmatchedPackets, hwCBQoSPolicyStatClassifierUnmatchedBytes,
            hwCBQoSPolicyStatClassifierMatchedPassPackets,hwCBQoSPolicyStatClassifierMatchedPassBytes,hwCBQoSPolicyStatClassifierMatchedDropPackets,hwCBQoSPolicyStatClassifierMatchedDropBytes }
        STATUS current
        DESCRIPTION 
            "This is a optional group of information."
        ::= { hwCBQoSGroups 54 }
        hwCBQoSVlanApplyPolicyGroup OBJECT-GROUP
            OBJECTS { hwCBQoSVlanApplyPolicyDirection, hwCBQoSVlanApplyPolicyName, hwCBQoSVlanApplyPolicyRowStatus, hwCBQoSVlanApplyPolicyVlanId }
            STATUS current
            DESCRIPTION 
                    "This is a optional group of information."
            ::= { hwCBQoSGroups 55 }

        
        hwCBQoSSVlanClassMatchGroup OBJECT-GROUP
            OBJECTS { hwCBQoSVlanClassMatchedPackets }
            STATUS current
            DESCRIPTION 
                    "This is a optional group of information."
            ::= { hwCBQoSGroups 56 }

        
        hwCBQoSSVlanCarMatchGroup OBJECT-GROUP
            OBJECTS { hwCBQoSVlanCarPassedPackets, hwCBQoSVlanCarDiscardedPackets  }
            STATUS current
            DESCRIPTION 
                    "This is a optional group of information."
            ::= { hwCBQoSGroups 57 }

    hwCBQoSRandomDiscardCfgInfoGroup OBJECT-GROUP
        OBJECTS { hwCBQoSRandomPercent, hwCBQoSRandomDiscardRowStatus }
        STATUS current
        DESCRIPTION 
            "Description."
        ::= { hwCBQoSGroups 58 }


        hwCBQoSDenyPacketLengthCfgInfoGroup OBJECT-GROUP
            OBJECTS { hwCBQoSDenyPacketLengthOptype, hwCBQoSDenyPacketLengthMax, hwCBQoSDenyPacketLengthMin, hwCBQoSDenyPacketLength,hwCBQoSDenyPacketLengthRowStatus }
            STATUS current
            DESCRIPTION 
                "Description."
            ::= { hwCBQoSGroups 59 }

        
        -- 1.3.6.1.4.1.2011.5.25.32.1.3.2.60
        hwCBQoSDAAStatisticsCfgInfoGroup OBJECT-GROUP
            OBJECTS { hwCBQoSDAAStatisticsSummary, hwCBQoSDAAStatisticsRowStatus }
            STATUS current
            DESCRIPTION 
                "Description."
            ::= { hwCBQoSGroups 60 }

        
        -- 1.3.6.1.4.1.2011.5.25.32.1.3.2.61
        hwCBQoSDAATariffLevelCfgInfoGroup OBJECT-GROUP
            OBJECTS { hwCBQoSDAATariffLevelValue, hwCBQoSDAATariffLevelRowStatus }
            STATUS current
            DESCRIPTION 
                "Description."
            ::= { hwCBQoSGroups 61 }
            
        --beg: mod by j00126783 for policy-alarm        
        -- 1.3.6.1.4.1.2011.5.25.32.1.3.2.62
        hwCBQoSRuleNotSupportAlarmGroup OBJECT-GROUP
            OBJECTS { hwCBQoSRuleDirection, hwCBQoSRuleSlotID, hwCBQoSRuleInfo }
            STATUS current
            DESCRIPTION 
                "Description."
            ::= { hwCBQoSGroups 62 }
            
        -- 1.3.6.1.4.1.2011.5.25.32.1.3.2.63
        hwCBQoSActionNotSupportAlarmGroup OBJECT-GROUP
            OBJECTS { hwCBQoSActionDirection, hwCBQoSActionSlotID, hwCBQoSActionInfo }
            STATUS current
            DESCRIPTION 
                "Description."
            ::= { hwCBQoSGroups 63 }    
        --end: mod by j00126783 for policy-alarm             

    hwCBQoSPolicyStatSubPolicyClassifierRunInfoGroup OBJECT-GROUP
        OBJECTS { 
                hwCBQoSSubPolicyStatClassifierMatchedPackets,
                hwCBQoSSubPolicyStatClassifierMatchedBytes,
                hwCBQoSSubPolicyStatClassifierPassPackets,
                hwCBQoSSubPolicyStatClassifierPassBytes ,
                hwCBQoSSubPolicyStatClassifierDropPackets,
                hwCBQoSSubPolicyStatClassifierDropBytes,
                hwCBQoSSubPolicyStatClassifierQueueMatchedPackets,
                hwCBQoSSubPolicyStatClassifierQueueMatchedBytes,
                hwCBQoSSubPolicyStatClassifierQueueEnqueuedPackets,
                hwCBQoSSubPolicyStatClassifierQueueEnqueuedBytes,
                hwCBQoSSubPolicyStatClassifierQueueDiscardedPackets,
                hwCBQoSSubPolicyStatClassifierQueueDiscardedBytes,
                hwCBQoSSubPolicyStatClassifierCarGreenPackets,
                hwCBQoSSubPolicyStatClassifierCarGreenBytes,
                hwCBQoSSubPolicyStatClassifierCarYellowPackets,
                hwCBQoSSubPolicyStatClassifierCarYellowBytes,
                hwCBQoSSubPolicyStatClassifierCarRedPackets,
                hwCBQoSSubPolicyStatClassifierCarRedBytes,
                hwCBQoSSubPolicyStatClassifierMatchedPacketsRate,
                hwCBQoSSubPolicyStatClassifierMatchedBytesRate,
                hwCBQoSSubPolicyStatClassifierMatchedPassPacketsRate,
                hwCBQoSSubPolicyStatClassifierMatchedPassBytesRate,
                hwCBQoSSubPolicyStatClassifierMatchedDropPacketsRate,
                hwCBQoSSubPolicyStatClassifierMatchedDropBytesRate,
                hwCBQoSSubPolicyStatClassifierQueueMatchedPacketsRate, 
                hwCBQoSSubPolicyStatClassifierQueueMatchedBytesRate, 
                hwCBQoSSubPolicyStatClassifierQueueEnqueuedPacketsRate, 
                hwCBQoSSubPolicyStatClassifierQueueEnqueuedBytesRate, 
                hwCBQoSSubPolicyStatClassifierQueueDiscardedPacketsRate, 
                hwCBQoSSubPolicyStatClassifierQueueDiscardedBytesRate, 
                hwCBQoSSubPolicyStatClassifierCarGreenPassedPacketsRate, 
                hwCBQoSSubPolicyStatClassifierCarGreenPassedBytesRate ,
                hwCBQoSSubPolicyStatClassifierCarYellowPassedPacketsRate, 
                hwCBQoSSubPolicyStatClassifierCarYellowPassedBytesRate, 
                hwCBQoSSubPolicyStatClassifierCarRedPassedPacketsRate ,
                hwCBQoSSubPolicyStatClassifierCarRedPassedBytesRate ,
                hwCBQoSSubPolicyClassName
                    }

        STATUS current
        DESCRIPTION 
            "This is a optional group of information."
        ::= { hwCBQoSGroups 64 }
		--add by zhangyong 00291234
		-- 1.3.6.1.4.1.2011.5.25.32.1.3.2.64	
		hwCBQoSGlobalAclNotSupportAlarmGroup OBJECT-GROUP
			OBJECTS { hwCBQoSGlobalAclDirection, hwCBQoSGlobalAclSlotID }
            STATUS current
            DESCRIPTION 
                "Description."
            ::= { hwCBQoSGroups 65 } 
           
        --Beg: mod by l00200458 on 20160528                        
        -- 1.3.6.1.4.1.2011.5.25.32.1.3.2.66
        hwCBQoSUpdateUserQueueResourceNotEnoughAlarmGroup OBJECT-GROUP
            OBJECTS { hwCBQoSUpdateUserQueueBehaviorName, hwCBQoSUpdateUserQueueSlotID, hwCBQoSUpdateUserQueueCir, hwCBQoSUpdateUserQueuePir }
            STATUS current
            DESCRIPTION 
                "Description."
            ::= { hwCBQoSGroups 66 }    
        hwCBQoSSetUserQueueResourceNotEnoughAlarmGroup OBJECT-GROUP
            OBJECTS { hwCBQoSSetUserQueueBehaviorName, hwCBQoSSetUserQueueSlotID }
            STATUS current
            DESCRIPTION 
                "Description."
            ::= { hwCBQoSGroups 67 }    
        --End: mod by l00200458 on 20160528                        

    END
