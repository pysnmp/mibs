ACOS-VCS-IMAGES-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		vcsImagesModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "vcsImagesModule OID for ACOS"
				::=  {  acosSchema 16 }

images		 OBJECT IDENTIFIER ::= { vcsImagesModule 1}

imagesOperImagesListTable OBJECT-TYPE
	 SYNTAX SEQUENCE OF ImagesOperImagesListEntry
	 MAX-ACCESS not-accessible
	 STATUS current
	 DESCRIPTION
		 "VCS Images Information from object 'vcs.images'"
	::= {images 2}

imagesOperImagesListEntry OBJECT-TYPE
	SYNTAX ImagesOperImagesListEntry
	MAX-ACCESS not-accessible
	STATUS current
	DESCRIPTION
		"The imagesOperImagesList entry:images-list"
	INDEX {
		imagesOperImagesListSlotId,
		imagesOperImagesListImagesListListId
	}
	::= { imagesOperImagesListTable 1}

ImagesOperImagesListEntry ::=
	SEQUENCE {
		imagesOperImagesListSlotId Integer32,
		imagesOperImagesListImagesListListId Integer32,
		imagesOperImagesListType	DisplayString,
		imagesOperImagesListImagesName	DisplayString
	}

imagesOperImagesListSlotId OBJECT-TYPE
	SYNTAX Integer32
	MAX-ACCESS read-only
	STATUS current
	DESCRIPTION
		""
	::= { imagesOperImagesListEntry 1}

imagesOperImagesListImagesListListId OBJECT-TYPE
	SYNTAX Integer32
	MAX-ACCESS read-only
	STATUS current
	DESCRIPTION
		""
	::= { imagesOperImagesListEntry 2}

imagesOperImagesListType OBJECT-TYPE
	SYNTAX DisplayString
	MAX-ACCESS read-only
	STATUS current
	DESCRIPTION
		"type"
	::= { imagesOperImagesListEntry 3}

imagesOperImagesListImagesName OBJECT-TYPE
	SYNTAX DisplayString
	MAX-ACCESS read-only
	STATUS current
	DESCRIPTION
		"images-name"
	::= { imagesOperImagesListEntry 4}

END
