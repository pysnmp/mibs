ACOS-GSLB-SERVICE-PORT-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		gslbServicePortModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "gslbServicePortModule OID for ACOS"
				::=  {  acosSchema 434 }

servicePort		 OBJECT IDENTIFIER ::= { gslbServicePortModule 1}

servicePortOperServicePortListTable OBJECT-TYPE
	 SYNTAX SEQUENCE OF ServicePortOperServicePortListEntry
	 MAX-ACCESS not-accessible
	 STATUS current
	 DESCRIPTION
		 " from object 'gslb.service-port'"
	::= {servicePort 2}

servicePortOperServicePortListEntry OBJECT-TYPE
	SYNTAX ServicePortOperServicePortListEntry
	MAX-ACCESS not-accessible
	STATUS current
	DESCRIPTION
		"The servicePortOperServicePortList entry:service-port-list"
	INDEX {
		servicePortOperServicePortListSlotId,
		servicePortOperServicePortListServicePortListListId
	}
	::= { servicePortOperServicePortListTable 1}

ServicePortOperServicePortListEntry ::=
	SEQUENCE {
		servicePortOperServicePortListSlotId Integer32,
		servicePortOperServicePortListServicePortListListId Integer32,
		servicePortOperServicePortListServicePortName	DisplayString,
		servicePortOperServicePortListAttributes	DisplayString,
		servicePortOperServicePortListState	DisplayString,
		servicePortOperServicePortListActiveRealServer	Integer32,
		servicePortOperServicePortListCurrentConnections	Integer32
	}

servicePortOperServicePortListSlotId OBJECT-TYPE
	SYNTAX Integer32
	MAX-ACCESS read-only
	STATUS current
	DESCRIPTION
		""
	::= { servicePortOperServicePortListEntry 1}

servicePortOperServicePortListServicePortListListId OBJECT-TYPE
	SYNTAX Integer32
	MAX-ACCESS read-only
	STATUS current
	DESCRIPTION
		""
	::= { servicePortOperServicePortListEntry 2}

servicePortOperServicePortListServicePortName OBJECT-TYPE
	SYNTAX DisplayString
	MAX-ACCESS read-only
	STATUS current
	DESCRIPTION
		"service-port-name"
	::= { servicePortOperServicePortListEntry 3}

servicePortOperServicePortListAttributes OBJECT-TYPE
	SYNTAX DisplayString
	MAX-ACCESS read-only
	STATUS current
	DESCRIPTION
		"attributes"
	::= { servicePortOperServicePortListEntry 4}

servicePortOperServicePortListState OBJECT-TYPE
	SYNTAX DisplayString
	MAX-ACCESS read-only
	STATUS current
	DESCRIPTION
		"state"
	::= { servicePortOperServicePortListEntry 5}

servicePortOperServicePortListActiveRealServer OBJECT-TYPE
	SYNTAX Integer32
	MAX-ACCESS read-only
	STATUS current
	DESCRIPTION
		"active-real-server"
	::= { servicePortOperServicePortListEntry 6}

servicePortOperServicePortListCurrentConnections OBJECT-TYPE
	SYNTAX Integer32
	MAX-ACCESS read-only
	STATUS current
	DESCRIPTION
		"current-connections"
	::= { servicePortOperServicePortListEntry 7}

END
