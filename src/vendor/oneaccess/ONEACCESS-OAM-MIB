--          *****************************
--          *                           *
--          *         ONEOS MIB         *
--          *                           *
--          *****************************
--
--          ONEOS_MIB_STD_V05.1.R005_E001
--
--          Creation date : 22/01/2003
--
--          Compatibility with ONEOS_V31
--
--          Compatibility with ONEOS_V32
--



     ONEACCESS-OAM-MIB DEFINITIONS ::= BEGIN 

     IMPORTS
		MODULE-IDENTITY, OBJECT-TYPE,Counter32,Unsigned32,Integer32,IpAddress	  
			FROM SNMPv2-SMI
		DisplayString 
			FROM RFC1213-MIB
		MODULE-COMPLIANCE, OBJECT-GROUP
			FROM SNMPv2-CONF
		TimeStamp,TimeInterval        
			FROM SNMPv2-TC
		InterfaceIndex, ifIndex   
			FROM IF-MIB
		atmVclEntry
			FROM ATM-MIB
 	    	oacExpIMAtmOamStatistics,oacMIBModules	  
			FROM ONEACCESS-GLOBAL-REG;
--
--
     oacOamMIBModule MODULE-IDENTITY
         LAST-UPDATED "201110270000Z"
        ORGANIZATION  " OneAccess "
         CONTACT-INFO
           "Pascal KESTELOOT
            Postal: ONE ACCESS
                    381 Avenue du Général de Gaulle
                    92140 Clamart, France
		    FRANCE

            Tel: (+33) 01 41 87 70 00
            Fax: (+33) 01 41 87 74 00

            E-mail: pascal.kesteloot@oneaccess-net.com"

         DESCRIPTION
                    	"Contact updated"
    	REVISION        "201110270000Z"

		DESCRIPTION
			"Fixed Minor correction added last revision."
		REVISION	"201007080001Z"
			
         DESCRIPTION
              "This MIB module describes IP ACL Management objects."
	
	::= { oacMIBModules 673 }
--
--
oacAtmOamStatObjects OBJECT IDENTIFIER ::= { oacExpIMAtmOamStatistics 1 }
oacAtmOamStatNotifications OBJECT IDENTIFIER ::= { oacExpIMAtmOamStatistics 2 }
oacAtmOamStatConformance OBJECT IDENTIFIER ::= { oacExpIMAtmOamStatistics 3 }

--
--
oacAtmOamStatSwitch OBJECT IDENTIFIER ::= { oacAtmOamStatObjects 1 }

oacAtmOamSwitchMaxConnections OBJECT-TYPE
		SYNTAX Unsigned32
		MAX-ACCESS read-only
		STATUS current
		DESCRIPTION 
			" Maximum number of authorised OAM configured connections"
	 ::= { oacAtmOamStatSwitch 1 }

oacAtmOamSwitchSegLoopback OBJECT-TYPE
		SYNTAX INTEGER { enable(1),disable(2)}
		MAX-ACCESS read-only
		STATUS current
		DESCRIPTION 
			" Enable segment loopback on this switch"
	 ::= { oacAtmOamStatSwitch 2 }

oacAtmOamSwitchEndLoopback OBJECT-TYPE
		SYNTAX INTEGER { enable(1),disable(2)}
		MAX-ACCESS read-only
		STATUS current
		DESCRIPTION 
			" Enable end to end loopback on this switch"
	 ::= { oacAtmOamStatSwitch 3 }

oacAtmOamSwitchAisRdiEnable OBJECT-TYPE
		SYNTAX INTEGER { enable(1),disable(2)}
		MAX-ACCESS read-only
		STATUS current
		DESCRIPTION 
			" Enable Remote Defect Indication OAM cell generation 
			 if an Alarm Indication Signal OAM cell is received, or if a 
			defect is detected on the switch"
	 ::= { oacAtmOamStatSwitch 4 }

oacAtmOamSwitchSegmentContinuityCheckEnable OBJECT-TYPE
		SYNTAX INTEGER { enable(1),disable(2)}
		MAX-ACCESS read-only
		STATUS current
		DESCRIPTION 
			" Enable Segment Loss of Continuity cells defect on the pvc. 
			Enable generation of segment Continuity Check cells on the switch."
	 ::= { oacAtmOamStatSwitch 5 }

oacAtmOamSwitchEndContinuityCheckEnable OBJECT-TYPE
		SYNTAX INTEGER { enable(1),disable(2)}
		MAX-ACCESS read-only
		STATUS current
		DESCRIPTION 
			" Enable End to End  Loss of Continuity cells defect on the pvc. 
			Enable generation of End to End Continuity Check cells on the switch."
	 ::= { oacAtmOamStatSwitch 6 }

oacAtmOamSwitchOamCellsReceived OBJECT-TYPE
		SYNTAX Counter32
		MAX-ACCESS read-only
		STATUS current
		DESCRIPTION 
			" Number of received OAM cells on the switch"
	 ::= { oacAtmOamStatSwitch 7 }

oacAtmOamSwitchOamCellsTransmitted OBJECT-TYPE
		SYNTAX Counter32
		MAX-ACCESS read-only
		STATUS current
		DESCRIPTION 
			" Number of transmitted OAM cells on the switch"
	 ::= { oacAtmOamStatSwitch 8 }

oacAtmOamSwitchCurrentConnections OBJECT-TYPE
		SYNTAX Unsigned32
		MAX-ACCESS read-only
		STATUS current
		DESCRIPTION 
			" Current number of  OAM configured connections"
	 ::= { oacAtmOamStatSwitch 9 }



--
--

oacAtmOamVclTable OBJECT-TYPE
	SYNTAX SEQUENCE OF OacAtmOamVclEntry
		MAX-ACCESS not-accessible
		STATUS current
		DESCRIPTION 
			"An index into the table oacAtmOamVclTable"
	 ::= { oacAtmOamStatObjects 2 }

oacAtmOamVclEntry OBJECT-TYPE
		SYNTAX OacAtmOamVclEntry
		MAX-ACCESS not-accessible
		STATUS current
		DESCRIPTION 
			"An index into the table oacAtmOamVclTable"
		AUGMENTS {atmVclEntry}
::= { oacAtmOamVclTable 1 }

OacAtmOamVclEntry ::= SEQUENCE {
oacAtmOamVclPvcManage INTEGER,
oacAtmOamVclSegmentLoopback INTEGER,
oacAtmOamVclEndLoopback INTEGER,
oacAtmOamVclAisRdiEnable INTEGER,
oacAtmOamVclSegmentContinuityCheckEnable INTEGER,
oacAtmOamVclEndContinuityCheckEnable INTEGER,
oacAtmOamVclLoopbackTxInterval Integer32,
oacAtmOamVclLoopbackTxRetryFrequency Integer32,
oacAtmOamVclLoopbackTxRetryUpCount Integer32,
oacAtmOamVclLoopbackTxRetryDownCount Integer32,
oacAtmOamVclAlarmState Integer32,
oacAtmOamVclAlarmStateLastChange TimeStamp,
oacAtmOamVclAisRdiRetryDownCount Integer32,
oacAtmOamVclAisRdiRetryUpTimer Integer32,
oacAtmOamVclPvcIntrusive INTEGER
}

oacAtmOamVclPvcManage OBJECT-TYPE
		SYNTAX INTEGER { enable(1),disable(2)}
		MAX-ACCESS read-only
		STATUS current
		DESCRIPTION 
			" Enable OAM for Pvc management"
	 ::= { oacAtmOamVclEntry 1 }

oacAtmOamVclSegmentLoopback OBJECT-TYPE
		SYNTAX INTEGER { enable(1),disable(2)}
		MAX-ACCESS read-only
		STATUS current
		DESCRIPTION 
			" Enable segment loopback on this virtual channel"
	 ::= { oacAtmOamVclEntry 2 }

oacAtmOamVclEndLoopback OBJECT-TYPE
		SYNTAX INTEGER { enable(1),disable(2)}
		MAX-ACCESS read-only
		STATUS current
		DESCRIPTION 
			" Enable end to end loopback on this virtual channel"
	 ::= { oacAtmOamVclEntry 3 }

oacAtmOamVclAisRdiEnable OBJECT-TYPE
		SYNTAX INTEGER { enable(1),disable(2)}
		MAX-ACCESS read-only
		STATUS current
		DESCRIPTION 
			" Enable Remote Defect Indication
			OAM cell generation if an Alarm
			Indication Signal OAM cell is received,
			or if a defect is detected on the PVC"
	 ::= { oacAtmOamVclEntry 4 }

oacAtmOamVclSegmentContinuityCheckEnable OBJECT-TYPE
		SYNTAX INTEGER { enable(1),disable(2)}
		MAX-ACCESS read-only
		STATUS current
		DESCRIPTION 
			" Enable Segment Loss of Continuity 
			cells detect on the PVC.Enable generation of
			Segment  Continuity Check
			cells  on the PVC."
	 ::= { oacAtmOamVclEntry 5 }

oacAtmOamVclEndContinuityCheckEnable OBJECT-TYPE
		SYNTAX INTEGER { enable(1),disable(2)}
		MAX-ACCESS read-only
		STATUS current
		DESCRIPTION 
			" Enable End to End Loss of Continuity 
			cells detect on the PVC.Enable generation of
			End to End  Continuity Check
			cells  on the PVC."
	 ::= { oacAtmOamVclEntry 6 }


oacAtmOamVclLoopbackTxInterval OBJECT-TYPE
		SYNTAX Integer32
		MAX-ACCESS read-only
		STATUS current
		DESCRIPTION 
			" Frequency of OAM loopback cell
			are generated on this virtual channel"
	 ::= { oacAtmOamVclEntry  7}

oacAtmOamVclLoopbackTxRetryFrequency OBJECT-TYPE
		SYNTAX Integer32
		MAX-ACCESS read-only
		STATUS current
		DESCRIPTION 
			" Frequency of OAM loopback cell
			are generated on this virtual channel,
			when a change has occured, that is to
			say either no reception of the last
			loopback cell, or reception of the 
			last loopback cell"
	 ::= { oacAtmOamVclEntry  8}

oacAtmOamVclLoopbackTxRetryUpCount OBJECT-TYPE
		SYNTAX Integer32
		MAX-ACCESS read-only
		STATUS current
		DESCRIPTION 
			" Counter of consecutive received loopback cells,
			before vcl is considered as being up"
	 ::= { oacAtmOamVclEntry  9}

oacAtmOamVclLoopbackTxRetryDownCount OBJECT-TYPE
		SYNTAX Integer32
		MAX-ACCESS read-only
		STATUS current
		DESCRIPTION 
			" Counter of consecutive non received loopback cells,
			before vcl is considered as being down"
	 ::= { oacAtmOamVclEntry  10}


oacAtmOamVclAlarmState  OBJECT-TYPE
		SYNTAX Integer32 		MAX-ACCESS read-only
		STATUS current
		DESCRIPTION 
			" This object indicates the current
			alarm status of the VCL, when error monitoring
			is activated on the VCL. Value indicates
			the different alarm states tha the VCL can take.
			Those alarms can be combined together.
			The unknown state indicates that the
			alarm status of this VCL cannot be determined.
			cc_seg_loc(1),cc_ete_loc(2),
			lb_seg_alarm(4),lb_ete_alarm(8),
			ais_alarm(16),rdi_alarm(32),other(64)"
	 ::= { oacAtmOamVclEntry 11 }

oacAtmOamVclAlarmStateLastChange OBJECT-TYPE
		SYNTAX TimeStamp
		MAX-ACCESS read-only
		STATUS current
		DESCRIPTION 
			" The value of sysUpTime object at the time this VCL
			entered its current alarm status. If the current state
			was entered prior to the last re-initialization of the
			agent, then this object contains a zero value."
	 ::= { oacAtmOamVclEntry  12}

oacAtmOamVclAisRdiRetryDownCount OBJECT-TYPE
		SYNTAX Integer32
		MAX-ACCESS read-only
		STATUS current
		DESCRIPTION 
			" Number of consecutive OAM AIS/RDI cells received.
			The range is 3 to 60. The default is 3."
	 ::= { oacAtmOamVclEntry  13}

oacAtmOamVclAisRdiRetryUpTimer OBJECT-TYPE
		SYNTAX Integer32
		MAX-ACCESS read-only
		STATUS current
		DESCRIPTION 
			" Number of seconds with no  OAM AIS/RDI cells received.
			The range is 3 to 60 seconds . The default is 3 seconds."
	 ::= { oacAtmOamVclEntry  14}

oacAtmOamVclPvcIntrusive OBJECT-TYPE
		SYNTAX INTEGER { enable(1),disable(2)}
		MAX-ACCESS read-only
		STATUS current
		DESCRIPTION 
			" Enable OAM Intrusivity against Pvc"
	 ::= { oacAtmOamVclEntry 15 }
--
--

oacAtmOamVclCountersTable OBJECT-TYPE
	SYNTAX SEQUENCE OF OacAtmOamVclCountersEntry
		MAX-ACCESS not-accessible
		STATUS current
		DESCRIPTION 
			"An index into table oacAtmOamVclCountersTable"
	 ::= { oacAtmOamStatObjects 3 }

oacAtmOamVclCountersEntry OBJECT-TYPE
		SYNTAX OacAtmOamVclCountersEntry
		MAX-ACCESS not-accessible
		STATUS current
		DESCRIPTION 
			"An index into table oacAtmOamVclCountersTable"
		AUGMENTS {atmVclEntry}
::= { oacAtmOamVclCountersTable 1 }

OacAtmOamVclCountersEntry ::= SEQUENCE {
oacAtmOamVclOamCellsReceived Counter32,
oacAtmOamVclEndLoopbackIn Counter32,
oacAtmOamVclSegLoopbackIn Counter32,
oacAtmOamVclEndLoopIn 	  Counter32,
oacAtmOamVclSegLoopIn  	  Counter32,
oacAtmOamVclAisIn  	  Counter32,
oacAtmOamVclRdiIn  	  Counter32,
oacAtmOamVclSegCCIn  	  Counter32,
oacAtmOamVclEndCCIn  	  Counter32,
oacAtmOamVclOamCellsSent 	  Counter32,
oacAtmOamVclEndLoopbackOut Counter32,
oacAtmOamVclSegLoopbackOut Counter32,
oacAtmOamVclEndLoopOut 	  Counter32,
oacAtmOamVclSegLoopOut 	  Counter32,
oacAtmOamVclAisOut  	  Counter32,
oacAtmOamVclRdiOut  	  Counter32,
oacAtmOamVclSegCCOut  	  Counter32,
oacAtmOamVclEndCCOut  	  Counter32,
oacAtmOamVclOamCellsDropped  Counter32
}

oacAtmOamVclOamCellsReceived OBJECT-TYPE
		SYNTAX  Counter32
		MAX-ACCESS read-only
		STATUS current
		DESCRIPTION 
			" Number of received oam cells"
	 ::= { oacAtmOamVclCountersEntry 1 }

oacAtmOamVclEndLoopbackIn OBJECT-TYPE
		SYNTAX  Counter32
		MAX-ACCESS read-only
		STATUS current
		DESCRIPTION 
			" Number of received non looped 
			end to end oam loopback cells "
	 ::= { oacAtmOamVclCountersEntry 2 }

oacAtmOamVclSegLoopbackIn OBJECT-TYPE
		SYNTAX  Counter32
		MAX-ACCESS read-only
		STATUS current
		DESCRIPTION 
			" Number of received non looped 
			segment oam loopback cells"
	 ::= { oacAtmOamVclCountersEntry 3 }

oacAtmOamVclEndLoopIn 	  OBJECT-TYPE
		SYNTAX  Counter32
		MAX-ACCESS read-only
		STATUS current
		DESCRIPTION 
			" Number of received looped end 
			to end oam loopback cells"
	 ::= { oacAtmOamVclCountersEntry 4 }

oacAtmOamVclSegLoopIn 	  OBJECT-TYPE
		SYNTAX  Counter32
		MAX-ACCESS read-only
		STATUS current
		DESCRIPTION 
			" Number of received looped segment 
			 oam loopback cells"
	 ::= { oacAtmOamVclCountersEntry 5 }


oacAtmOamVclAisIn 	  OBJECT-TYPE
		SYNTAX  Counter32
		MAX-ACCESS read-only
		STATUS current
		DESCRIPTION 
			" Number of received oam ais cells"
	 ::= { oacAtmOamVclCountersEntry 6 }

oacAtmOamVclRdiIn 	  OBJECT-TYPE
		SYNTAX  Counter32
		MAX-ACCESS read-only
		STATUS current
		DESCRIPTION 
			" Number of received oam rdi cells"
	 ::= { oacAtmOamVclCountersEntry 7 }

oacAtmOamVclSegCCIn 	  OBJECT-TYPE
		SYNTAX  Counter32
		MAX-ACCESS read-only
		STATUS current
		DESCRIPTION 
			" Number of received oam end to end continuity check  cells"
	 ::= { oacAtmOamVclCountersEntry 8 }

oacAtmOamVclEndCCIn 	  OBJECT-TYPE
		SYNTAX  Counter32
		MAX-ACCESS read-only
		STATUS current
		DESCRIPTION 
			" Number of received oam segment continuity check  cells"
	 ::= { oacAtmOamVclCountersEntry 9 }

oacAtmOamVclOamCellsSent 	  OBJECT-TYPE
		SYNTAX  Counter32
		MAX-ACCESS read-only
		STATUS current
		DESCRIPTION 
			" Number of sent oam cells"
	 ::= { oacAtmOamVclCountersEntry 10 }

oacAtmOamVclEndLoopbackOut 	  OBJECT-TYPE
		SYNTAX  Counter32
		MAX-ACCESS read-only
		STATUS current
		DESCRIPTION 
			" Number of sent non looped end to end oam loopback cells "
	 ::= { oacAtmOamVclCountersEntry 11 }

oacAtmOamVclSegLoopbackOut 	  OBJECT-TYPE
		SYNTAX  Counter32
		MAX-ACCESS read-only
		STATUS current
		DESCRIPTION 
			" Number of sent non looped segment oam loopback cells"
	 ::= { oacAtmOamVclCountersEntry 12 }

oacAtmOamVclEndLoopOut 	  OBJECT-TYPE
		SYNTAX  Counter32
		MAX-ACCESS read-only
		STATUS current
		DESCRIPTION 
			" Number of sent looped end to end oam loopback cells"
	 ::= { oacAtmOamVclCountersEntry 13 }

oacAtmOamVclSegLoopOut 	  OBJECT-TYPE
		SYNTAX  Counter32
		MAX-ACCESS read-only
		STATUS current
		DESCRIPTION 
			" Number of sent looped segment oam loopback cells"
	 ::= { oacAtmOamVclCountersEntry 14 }


oacAtmOamVclAisOut 	  OBJECT-TYPE
		SYNTAX Counter32
		MAX-ACCESS read-only
		STATUS current
		DESCRIPTION 
			" Number of sent oam ais cells"
	 ::= { oacAtmOamVclCountersEntry 15 }

oacAtmOamVclRdiOut 	  OBJECT-TYPE
		SYNTAX  Counter32
		MAX-ACCESS read-only
		STATUS current
		DESCRIPTION 
			" Number of sent oam rdi cells"
	 ::= { oacAtmOamVclCountersEntry 16 }

oacAtmOamVclSegCCOut 	  OBJECT-TYPE
		SYNTAX  Counter32
		MAX-ACCESS read-only
		STATUS current
		DESCRIPTION 
			" Number of sent oam end to end continuity check  cells"
	 ::= { oacAtmOamVclCountersEntry 17 }

oacAtmOamVclEndCCOut 	  OBJECT-TYPE
		SYNTAX  Counter32
		MAX-ACCESS read-only
		STATUS current
		DESCRIPTION 
			" Number of sent oam segment continuity check  cells	"
	 ::= { oacAtmOamVclCountersEntry 18 }

oacAtmOamVclOamCellsDropped  	  OBJECT-TYPE
		SYNTAX  Counter32
		MAX-ACCESS read-only
		STATUS current
		DESCRIPTION 
			" Number of received oam cells that are ignored and dropped"
	 ::= { oacAtmOamVclCountersEntry 19 }



--
--

oacAtmOamStatGroups OBJECT IDENTIFIER ::= { oacAtmOamStatConformance 1}


oacAtmOamStatCompliances OBJECT IDENTIFIER ::= { oacAtmOamStatConformance 2}

oacAtmOamStatCompliance MODULE-COMPLIANCE
      STATUS  current
      DESCRIPTION
          "The compliance statement for agents that support the
          ONEACCESS-OAM-MIB."
      MODULE -- this module
          MANDATORY-GROUPS { oacAtmOamStatGeneralGroup
                }

	::= { oacAtmOamStatCompliances 1}

oacAtmOamStatGeneralGroup OBJECT-GROUP
	OBJECTS {
oacAtmOamSwitchMaxConnections,
oacAtmOamSwitchSegLoopback,
oacAtmOamSwitchEndLoopback,
oacAtmOamSwitchAisRdiEnable,
oacAtmOamSwitchSegmentContinuityCheckEnable,
oacAtmOamSwitchEndContinuityCheckEnable,
oacAtmOamSwitchOamCellsReceived,
oacAtmOamSwitchOamCellsTransmitted,
oacAtmOamSwitchCurrentConnections,
oacAtmOamVclPvcManage ,
oacAtmOamVclSegmentLoopback ,
oacAtmOamVclEndLoopback ,
oacAtmOamVclAisRdiEnable ,
oacAtmOamVclSegmentContinuityCheckEnable ,
oacAtmOamVclEndContinuityCheckEnable ,
oacAtmOamVclLoopbackTxInterval ,
oacAtmOamVclLoopbackTxRetryFrequency ,
oacAtmOamVclLoopbackTxRetryUpCount ,
oacAtmOamVclLoopbackTxRetryDownCount ,
oacAtmOamVclAlarmState ,
oacAtmOamVclAlarmStateLastChange ,
oacAtmOamVclAisRdiRetryDownCount ,
oacAtmOamVclAisRdiRetryUpTimer ,
oacAtmOamVclPvcIntrusive ,
oacAtmOamVclOamCellsReceived ,
oacAtmOamVclEndLoopbackIn ,
oacAtmOamVclSegLoopbackIn ,
oacAtmOamVclEndLoopIn 	  ,
oacAtmOamVclSegLoopIn  	  ,
oacAtmOamVclAisIn  	  ,
oacAtmOamVclRdiIn  	  ,
oacAtmOamVclSegCCIn  	  ,
oacAtmOamVclEndCCIn  	  ,
oacAtmOamVclOamCellsSent 	  ,
oacAtmOamVclEndLoopbackOut ,
oacAtmOamVclSegLoopbackOut ,
oacAtmOamVclEndLoopOut 	  ,
oacAtmOamVclSegLoopOut 	  ,
oacAtmOamVclAisOut  	  ,
oacAtmOamVclRdiOut  	  ,
oacAtmOamVclSegCCOut  	  ,
oacAtmOamVclEndCCOut  	  ,
oacAtmOamVclOamCellsDropped  
}

STATUS  current
      DESCRIPTION
          "This group is mandatory for all  OAM entities."
      ::= { oacAtmOamStatGroups 1 }


END
--
