--
-- IRT-FM-ACTIVERESERVE-MIB.my
-- MIB generated by MG-SOFT Visual MIB Builder Version 6.0  Build 88
-- Friday, May 04, 2007 at 17:20:39
--

	IRT-FM-ACTIVERESERVE-MIB DEFINITIONS ::= BEGIN
 
		IMPORTS
			eventTimeStamp, eventPriority, eventCounter, mibRelease			
				FROM IRT-COMMONVARBINDS-MIB			
			fm, SelectOnOff, LocalRemote, FaultOK, SelectManualAuto, 
			ReadyNotReady, ExecutedNotExecuted, PresentNotPresent, WarningOK			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DisplayString, TruthValue			
				FROM SNMPv2-TC;
	
	
		-- 1.3.6.1.4.1.19831.1.1.3.2
		fmActiveReserve MODULE-IDENTITY 
			LAST-UPDATED "200705041400Z"		-- May 04, 2007 at 14:00 GMT
			ORGANIZATION 
				"IRT-WORKING-GROUP-TC-MIB"
			CONTACT-INFO 
				"Contact-info.
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				
				branch definition
				
				1st level
				
				events              OBJECT IDENTIFIER ::= { fmActiveReserve 0 }
				fmARGeneral         OBJECT IDENTIFIER ::= { fmActiveReserve 1 }
				fmARAmplifierA      OBJECT IDENTIFIER ::= { fmActiveReserve 2 }
				fmARAmplifierB      OBJECT IDENTIFIER ::= { fmActiveReserve 3 }
				fmARExciterA        OBJECT IDENTIFIER ::= { fmActiveReserve 4 }
				fmRExciterB         OBJECT IDENTIFIER ::= { fmActiveReserve 5 }
				fmAREventEnable     OBJECT IDENTIFIER ::= { fmActiveReserve 6 }
				fmAREventPriority   OBJECT IDENTIFIER ::= { fmActiveReserve 7 }
				groups              OBJECT IDENTIFIER ::= { fmActiveReserve 8 }
				
				2nd level
				
				fmAREventEnableGeneral     OBJECT IDENTIFIER ::= { fmAREventEnable 1 }
				fmAREventEnableAmplifierA  OBJECT IDENTIFIER ::= { fmAREventEnable 2 }
				fmAREventEnableAmplifierB  OBJECT IDENTIFIER ::= { fmAREventEnable 3 }
				fmAREventEnableExciterA    OBJECT IDENTIFIER ::= { fmAREventEnable 4 }
				fmAREventEnableExciterB    OBJECT IDENTIFIER ::= { fmAREventEnable 5 }
				
				fmAREventPriorityGeneral     OBJECT IDENTIFIER ::= { fmAREventPriority 1 }
				fmAREventPriorityAmplifierA  OBJECT IDENTIFIER ::= { fmAREventPriority 2 }
				fmAREventPriorityAmplifierB  OBJECT IDENTIFIER ::= { fmAREventPriority 3 }
				fmAREventPriorityExciterA    OBJECT IDENTIFIER ::= { fmAREventPriority 4 }
				fmAREventPriorityExciterB    OBJECT IDENTIFIER ::= { fmAREventPriority 5 }
				
				end branch"
			REVISION "200705041400Z"		-- May 04, 2007 at 14:00 GMT
			DESCRIPTION 
				"change LocalMode (description only) and Module-COMPLIANCE
				change numbering: OIDs 1.3.6.1.4.1.19831.1.1.3.2.6.1.10-16 and 
				1.3.6.1.4.1.19831.1.1.3.2.7.1.10-16!
				"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { fm 2 }

		
	
	
--
-- Node definitions
--
	
-- Events active reserve
		-- 1.3.6.1.4.1.19831.1.1.3.2.0
		fmEventsAR OBJECT IDENTIFIER ::= { fmActiveReserve 0 }

		
		-- 1.3.6.1.4.1.19831.1.1.3.2.0.1
		fmARPreselectionExciterEvent NOTIFICATION-TYPE
			OBJECTS { sysDescr, sysName, sysLocation, eventTimeStamp, eventPriority, 
				eventCounter, fmARPreselectionExciter }
			STATUS current
			DESCRIPTION 
				"Description. fmARPreselectionExciter notification"
			::= { fmEventsAR 1 }

		
		-- 1.3.6.1.4.1.19831.1.1.3.2.0.2
		fmARPreselectionAmplifierEvent NOTIFICATION-TYPE
			OBJECTS { sysDescr, sysName, sysLocation, eventTimeStamp, eventPriority, 
				eventCounter, fmARPreselectionAmplifier }
			STATUS current
			DESCRIPTION 
				"Description. fmARPreselectionAmplifier notification"
			::= { fmEventsAR 2 }

		
		-- 1.3.6.1.4.1.19831.1.1.3.2.0.3
		fmARTransmitterOpModeEvent NOTIFICATION-TYPE
			OBJECTS { sysDescr, sysName, sysLocation, eventTimeStamp, eventPriority, 
				eventCounter, fmARTransmitterOpMode }
			STATUS current
			DESCRIPTION 
				"Description. fmARTransmitterOpMode notification"
			::= { fmEventsAR 3 }

		
		-- 1.3.6.1.4.1.19831.1.1.3.2.0.4
		fmARReserveControlEvent NOTIFICATION-TYPE
			OBJECTS { sysDescr, sysName, sysLocation, eventTimeStamp, eventPriority, 
				eventCounter, fmARReserveControl }
			STATUS current
			DESCRIPTION 
				"Description. fmARReserveControl notification"
			::= { fmEventsAR 4 }

		
		-- 1.3.6.1.4.1.19831.1.1.3.2.0.5
		fmARActiveAmplifierEvent NOTIFICATION-TYPE
			OBJECTS { sysDescr, sysName, sysLocation, eventTimeStamp, eventPriority, 
				eventCounter, fmARActiveAmplifier }
			STATUS current
			DESCRIPTION 
				"Description. fmARActiveAmplifier notification"
			::= { fmEventsAR 5 }

		
		-- 1.3.6.1.4.1.19831.1.1.3.2.0.6
		fmARActiveExciterEvent NOTIFICATION-TYPE
			OBJECTS { sysDescr, sysName, sysLocation, eventTimeStamp, eventPriority, 
				eventCounter, fmARActiveExciter }
			STATUS current
			DESCRIPTION 
				"Description. fmARActiveExciter notification"
			::= { fmEventsAR 6 }

		
		-- 1.3.6.1.4.1.19831.1.1.3.2.0.7
		fmARLocalModeEvent NOTIFICATION-TYPE
			OBJECTS { sysDescr, sysName, sysLocation, eventTimeStamp, eventPriority, 
				eventCounter, fmARLocalMode }
			STATUS current
			DESCRIPTION 
				"Description. fmARLocalMode notification"
			::= { fmEventsAR 7 }

		
		-- 1.3.6.1.4.1.19831.1.1.3.2.0.8
		fmARControlUnitFaultEvent NOTIFICATION-TYPE
			OBJECTS { sysDescr, sysName, sysLocation, eventTimeStamp, eventPriority, 
				eventCounter, fmARControlUnitFault }
			STATUS current
			DESCRIPTION 
				"Description. fmARControlUnitFault notification"
			::= { fmEventsAR 8 }

		
		-- 1.3.6.1.4.1.19831.1.1.3.2.0.9
		fmARExciterSwitchOverModeEvent NOTIFICATION-TYPE
			OBJECTS { sysDescr, sysName, sysLocation, eventTimeStamp, eventPriority, 
				eventCounter, fmARExciterSwitchOverMode }
			STATUS current
			DESCRIPTION 
				"Description. fmARExciterSwitchOverMode notification"
			::= { fmEventsAR 9 }

		
		-- 1.3.6.1.4.1.19831.1.1.3.2.0.10
		fmARExciterSwitchOverReadyEvent NOTIFICATION-TYPE
			OBJECTS { sysDescr, sysName, sysLocation, eventTimeStamp, eventPriority, 
				eventCounter, fmARExciterSwitchOverReady }
			STATUS current
			DESCRIPTION 
				"Description. fmARExciterSwitchOverReady notification"
			::= { fmEventsAR 10 }

		
		-- 1.3.6.1.4.1.19831.1.1.3.2.0.11
		fmARExciterSwitchOverExecutedEvent NOTIFICATION-TYPE
			OBJECTS { sysDescr, sysName, sysLocation, eventTimeStamp, eventPriority, 
				eventCounter, fmARExciterSwitchOverExecuted }
			STATUS current
			DESCRIPTION 
				"Description. fmARExciterSwitchOverExecuted notification"
			::= { fmEventsAR 11 }

		
		-- 1.3.6.1.4.1.19831.1.1.3.2.0.12
		fmARExciterSwitchOverFaultEvent NOTIFICATION-TYPE
			OBJECTS { sysDescr, sysName, sysLocation, eventTimeStamp, eventPriority, 
				eventCounter, fmARExciterSwitchOverFault }
			STATUS current
			DESCRIPTION 
				"Description. fmARExciterSwitchOverFault notification"
			::= { fmEventsAR 12 }

		
		-- 1.3.6.1.4.1.19831.1.1.3.2.0.13
		fmARAmplifierSwitchOverModeEvent NOTIFICATION-TYPE
			OBJECTS { sysDescr, sysName, sysLocation, eventTimeStamp, eventPriority, 
				eventCounter, fmARAmplifierSwitchOverMode }
			STATUS current
			DESCRIPTION 
				"Description. fmARAmplifierSwitchOverMode notification"
			::= { fmEventsAR 13 }

		
		-- 1.3.6.1.4.1.19831.1.1.3.2.0.14
		fmARAmplifierSwitchOverReadyEvent NOTIFICATION-TYPE
			OBJECTS { sysDescr, sysName, sysLocation, eventTimeStamp, eventPriority, 
				eventCounter, fmARAmplifierSwitchOverReady }
			STATUS current
			DESCRIPTION 
				"Description. fmARAmplifierSwitchOverReady notification"
			::= { fmEventsAR 14 }

		
		-- 1.3.6.1.4.1.19831.1.1.3.2.0.15
		fmARAmplifierSwitchOverExecutedEvent NOTIFICATION-TYPE
			OBJECTS { sysDescr, sysName, sysLocation, eventTimeStamp, eventPriority, 
				eventCounter, fmARAmplifierSwitchOverExecuted }
			STATUS current
			DESCRIPTION 
				"Description. fmARAmplifierSwitchOverExecuted notification"
			::= { fmEventsAR 15 }

		
		-- 1.3.6.1.4.1.19831.1.1.3.2.0.16
		fmARAmplifierSwitchOverFaultEvent NOTIFICATION-TYPE
			OBJECTS { sysDescr, sysName, sysLocation, eventTimeStamp, eventPriority, 
				eventCounter, fmARAmplifierSwitchOverFault }
			STATUS current
			DESCRIPTION 
				"Description. fmARAmplifierSwitchOverFault notification"
			::= { fmEventsAR 16 }

		
		-- 1.3.6.1.4.1.19831.1.1.3.2.0.17
		fmARAmplifierARFPresentEvent NOTIFICATION-TYPE
			OBJECTS { sysDescr, sysName, sysLocation, eventTimeStamp, eventPriority, 
				eventCounter, fmARAmplifierARFPresent }
			STATUS current
			DESCRIPTION 
				"Description. fmARAmplifierARFPresent notification"
			::= { fmEventsAR 17 }

		
		-- 1.3.6.1.4.1.19831.1.1.3.2.0.18
		fmARAmplifierAFaultEvent NOTIFICATION-TYPE
			OBJECTS { sysDescr, sysName, sysLocation, eventTimeStamp, eventPriority, 
				eventCounter, fmARAmplifierAFault }
			STATUS current
			DESCRIPTION 
				"Description. fmARAmplifierAFault notification"
			::= { fmEventsAR 18 }

		
		-- 1.3.6.1.4.1.19831.1.1.3.2.0.19
		fmARAmplifierAWarningEvent NOTIFICATION-TYPE
			OBJECTS { sysDescr, sysName, sysLocation, eventTimeStamp, eventPriority, 
				eventCounter, fmARAmplifierAWarning }
			STATUS current
			DESCRIPTION 
				"Description. fmARAmplifierAWarning notification"
			::= { fmEventsAR 19 }

		
		-- 1.3.6.1.4.1.19831.1.1.3.2.0.20
		fmARAmplifierBRFPresentEvent NOTIFICATION-TYPE
			OBJECTS { sysDescr, sysName, sysLocation, eventTimeStamp, eventPriority, 
				eventCounter, fmARAmplifierBRFPresent }
			STATUS current
			DESCRIPTION 
				"Description. fmARAmplifierBRFPresent notification"
			::= { fmEventsAR 20 }

		
		-- 1.3.6.1.4.1.19831.1.1.3.2.0.21
		fmARAmplifierBFaultEvent NOTIFICATION-TYPE
			OBJECTS { sysDescr, sysName, sysLocation, eventTimeStamp, eventPriority, 
				eventCounter, fmARAmplifierBFault }
			STATUS current
			DESCRIPTION 
				"Description. fmARAmplifierBFault notification"
			::= { fmEventsAR 21 }

		
		-- 1.3.6.1.4.1.19831.1.1.3.2.0.22
		fmARAmplifierBWarningEvent NOTIFICATION-TYPE
			OBJECTS { sysDescr, sysName, sysLocation, eventTimeStamp, eventPriority, 
				eventCounter, fmARAmplifierBWarning }
			STATUS current
			DESCRIPTION 
				"Description. fmARAmplifierBWarning notification"
			::= { fmEventsAR 22 }

		
		-- 1.3.6.1.4.1.19831.1.1.3.2.0.23
		fmARExciterALocalModeEvent NOTIFICATION-TYPE
			OBJECTS { sysDescr, sysName, sysLocation, eventTimeStamp, eventPriority, 
				eventCounter, fmARExciterALocalMode }
			STATUS current
			DESCRIPTION 
				"Description. fmARExciterALocalMode notification"
			::= { fmEventsAR 23 }

		
		-- 1.3.6.1.4.1.19831.1.1.3.2.0.24
		fmARExciterAFaultEvent NOTIFICATION-TYPE
			OBJECTS { sysDescr, sysName, sysLocation, eventTimeStamp, eventPriority, 
				eventCounter, fmARExciterAFault }
			STATUS current
			DESCRIPTION 
				"Description. fmARExciterAFault notification"
			::= { fmEventsAR 24 }

		
		-- 1.3.6.1.4.1.19831.1.1.3.2.0.25
		fmARExciterAWarningEvent NOTIFICATION-TYPE
			OBJECTS { sysDescr, sysName, sysLocation, eventTimeStamp, eventPriority, 
				eventCounter, fmARExciterAWarning }
			STATUS current
			DESCRIPTION 
				"Description. fmARExciterAWarning notification"
			::= { fmEventsAR 25 }

		
		-- 1.3.6.1.4.1.19831.1.1.3.2.0.26
		fmARExciterBLocalModeEvent NOTIFICATION-TYPE
			OBJECTS { sysDescr, sysName, sysLocation, eventTimeStamp, eventPriority, 
				eventCounter, fmARExciterBLocalMode }
			STATUS current
			DESCRIPTION 
				"Description. fmARExciterBLocalMode notification"
			::= { fmEventsAR 26 }

		
		-- 1.3.6.1.4.1.19831.1.1.3.2.0.27
		fmARExciterBFaultEvent NOTIFICATION-TYPE
			OBJECTS { sysDescr, sysName, sysLocation, eventTimeStamp, eventPriority, 
				eventCounter, fmARExciterBFault }
			STATUS current
			DESCRIPTION 
				"Description. fmARExciterBFault notification"
			::= { fmEventsAR 27 }

		
		-- 1.3.6.1.4.1.19831.1.1.3.2.0.28
		fmARExciterBWarningEvent NOTIFICATION-TYPE
			OBJECTS { sysDescr, sysName, sysLocation, eventTimeStamp, eventPriority, 
				eventCounter, fmARExciterBWarning }
			STATUS current
			DESCRIPTION 
				"Description. fmARExciterBWarning notification"
			::= { fmEventsAR 28 }

		
-- fm active reserve general
		-- 1.3.6.1.4.1.19831.1.1.3.2.1
		fmARGeneral OBJECT IDENTIFIER ::= { fmActiveReserve 1 }

		
		-- 1.3.6.1.4.1.19831.1.1.3.2.1.1
		fmARPreselectionExciter OBJECT-TYPE
			SYNTAX INTEGER
				{
				undefined(0),
				exciterA(1),
				exciterB(2)
				}
			MAX-ACCESS read-write
			STATUS current
			DESCRIPTION
				"Aktive reserve. Preselection of the exciter
				
				
				"
			::= { fmARGeneral 1 }

		
		-- 1.3.6.1.4.1.19831.1.1.3.2.1.2
		fmARPreselectionAmplifier OBJECT-TYPE
			SYNTAX INTEGER
				{
				undefined(0),
				amplifierA(1),
				amplifierB(2),
				amplifierAB(3),
				amplifierABtodummyload(4)
				}
			MAX-ACCESS read-write
			STATUS current
			DESCRIPTION
				"Aktive reserve. Preselection amplifier 
				
				"
			::= { fmARGeneral 2 }

		
		-- 1.3.6.1.4.1.19831.1.1.3.2.1.3
		fmARTransmitterOpMode OBJECT-TYPE
			SYNTAX SelectOnOff
			MAX-ACCESS read-write
			STATUS current
			DESCRIPTION
				"General transmitter control of aktive reserve
				
				(0) undefined
				(1) ON
				(2) OFF"
			::= { fmARGeneral 3 }

		
		-- 1.3.6.1.4.1.19831.1.1.3.2.1.4
		fmARReserveControl OBJECT-TYPE
			SYNTAX SelectOnOff
			MAX-ACCESS read-write
			STATUS current
			DESCRIPTION
				"Reserve control of aktive reserve
				
				(0) undefined
				(1) ON 
				(2) OFF "
			::= { fmARGeneral 4 }

		
		-- 1.3.6.1.4.1.19831.1.1.3.2.1.5
		fmARActiveAmplifier OBJECT-TYPE
			SYNTAX INTEGER
				{
				undefined(0),
				amplifierA(1),
				amplifierB(2),
				amplifierAB(3),
				amplifierABtoDummyload(4)
				}
			MAX-ACCESS read-only
			STATUS current
			DESCRIPTION
				"Active amplifier  of aktive reserve
				
				"
			::= { fmARGeneral 5 }

		
		-- 1.3.6.1.4.1.19831.1.1.3.2.1.6
		fmARActiveExciter OBJECT-TYPE
			SYNTAX INTEGER
				{
				undefined(0),
				exciterA(1),
				exciterB(2)
				}
			MAX-ACCESS read-only
			STATUS current
			DESCRIPTION
				"Active exciter  of aktive reserve
				
				"
			::= { fmARGeneral 6 }

		
		-- 1.3.6.1.4.1.19831.1.1.3.2.1.7
		fmARLocalMode OBJECT-TYPE
			SYNTAX LocalRemote
			MAX-ACCESS read-only
			STATUS current
			DESCRIPTION
				"Active reserve. Local mode
				
				(0) undefined
				(1) local
				(2) remote"
			::= { fmARGeneral 7 }

		
		-- 1.3.6.1.4.1.19831.1.1.3.2.1.8
		fmARControlUnitFault OBJECT-TYPE
			SYNTAX FaultOK
			UNITS " "
			MAX-ACCESS read-only
			STATUS current
			DESCRIPTION
				"Aktive reserve. State of the control unit
				
				(0) undefined
				(1) fault
				(2) ok"
			::= { fmARGeneral 8 }

		
		-- 1.3.6.1.4.1.19831.1.1.3.2.1.9
		fmARExciterSwitchOverMode OBJECT-TYPE
			SYNTAX SelectManualAuto
			MAX-ACCESS read-write
			STATUS current
			DESCRIPTION
				"Aktive reserve. Exciter switch over mode: manual or automatic
				
				(0) undefined
				(1) manual 
				(2) automatic"
			::= { fmARGeneral 9 }

		
		-- 1.3.6.1.4.1.19831.1.1.3.2.1.10
		fmARExciterSwitchOverReady OBJECT-TYPE
			SYNTAX ReadyNotReady
			MAX-ACCESS read-only
			STATUS current
			DESCRIPTION
				"Aktive reserve. State of the exciter switch over unit
				
				(0) undefined
				(1) ready
				(2) not ready"
			::= { fmARGeneral 10 }

		
		-- 1.3.6.1.4.1.19831.1.1.3.2.1.11
		fmARExciterSwitchOverExecuted OBJECT-TYPE
			SYNTAX ExecutedNotExecuted
			MAX-ACCESS read-only
			STATUS current
			DESCRIPTION
				"Aktive reserve. Shows if the exciter switch over unit it has executed
				
				(0) undefined
				(1) executed
				(2) not executed"
			::= { fmARGeneral 11 }

		
		-- 1.3.6.1.4.1.19831.1.1.3.2.1.12
		fmARExciterSwitchOverFault OBJECT-TYPE
			SYNTAX FaultOK
			MAX-ACCESS read-only
			STATUS current
			DESCRIPTION
				"Aktive reserve. Fault state of the exciter switch over unit
				
				(0) undefined
				(1) faulty
				(2) ok"
			::= { fmARGeneral 12 }

		
		-- 1.3.6.1.4.1.19831.1.1.3.2.1.13
		fmARAmplifierSwitchOverMode OBJECT-TYPE
			SYNTAX SelectManualAuto
			MAX-ACCESS read-write
			STATUS current
			DESCRIPTION
				"Active reserve. Amplifier switch over mode: manual or automatic
				
				(0) undefined
				(1) manual
				(2) automatic"
			::= { fmARGeneral 13 }

		
		-- 1.3.6.1.4.1.19831.1.1.3.2.1.14
		fmARAmplifierSwitchOverReady OBJECT-TYPE
			SYNTAX ReadyNotReady
			MAX-ACCESS read-only
			STATUS current
			DESCRIPTION
				"Active reserve. State of the amplifier switch over unit
				
				(0) undefined
				(1) ready
				(2) not ready"
			::= { fmARGeneral 14 }

		
		-- 1.3.6.1.4.1.19831.1.1.3.2.1.15
		fmARAmplifierSwitchOverExecuted OBJECT-TYPE
			SYNTAX ExecutedNotExecuted
			MAX-ACCESS read-only
			STATUS current
			DESCRIPTION
				"Active reserve. Shows if the amplifier switch over unit it has executed
				
				(0) undefined
				(1) executed
				(2) not executed"
			::= { fmARGeneral 15 }

		
		-- 1.3.6.1.4.1.19831.1.1.3.2.1.16
		fmARAmplifierSwitchOverFault OBJECT-TYPE
			SYNTAX FaultOK
			MAX-ACCESS read-only
			STATUS current
			DESCRIPTION
				"Active reserve. Fault state of the amplifier switch over unit
				
				(0) undefined
				(1) faulty
				(2) ok"
			::= { fmARGeneral 16 }

		
-- fm active reserve amplifier A
		-- 1.3.6.1.4.1.19831.1.1.3.2.2
		fmARAmplifierA OBJECT IDENTIFIER ::= { fmActiveReserve 2 }

		
		-- 1.3.6.1.4.1.19831.1.1.3.2.2.1
		fmARAmplifierARFPresent OBJECT-TYPE
			SYNTAX PresentNotPresent
			MAX-ACCESS read-only
			STATUS current
			DESCRIPTION
				"Active reserve. Describes if the output power of the amplifier A is present
				
				(0) undefined
				(1) present
				(2) not present"
			::= { fmARAmplifierA 1 }

		
		-- 1.3.6.1.4.1.19831.1.1.3.2.2.2
		fmARAmplifierAFault OBJECT-TYPE
			SYNTAX FaultOK
			MAX-ACCESS read-only
			STATUS current
			DESCRIPTION
				"Active reserve. Fault state of amplifier A
				
				(0) undefined
				(1) fault
				(2) ok"
			::= { fmARAmplifierA 2 }

		
		-- 1.3.6.1.4.1.19831.1.1.3.2.2.3
		fmARAmplifierAWarning OBJECT-TYPE
			SYNTAX WarningOK
			MAX-ACCESS read-only
			STATUS current
			DESCRIPTION
				"Active reserve. Warning state of amplifier A
				
				(0) undefined
				(1) warning
				(2) ok"
			::= { fmARAmplifierA 3 }

		
-- fm active reserve amplifier B
		-- 1.3.6.1.4.1.19831.1.1.3.2.3
		fmARAmplifierB OBJECT IDENTIFIER ::= { fmActiveReserve 3 }

		
		-- 1.3.6.1.4.1.19831.1.1.3.2.3.1
		fmARAmplifierBRFPresent OBJECT-TYPE
			SYNTAX PresentNotPresent
			MAX-ACCESS read-only
			STATUS current
			DESCRIPTION
				"Active reserve. Describes if the output power of the amplifier B is present
				
				(0) undefined
				(1) present
				(2) not present"
			::= { fmARAmplifierB 1 }

		
		-- 1.3.6.1.4.1.19831.1.1.3.2.3.2
		fmARAmplifierBFault OBJECT-TYPE
			SYNTAX FaultOK
			MAX-ACCESS read-only
			STATUS current
			DESCRIPTION
				"Active reserve. Fault state of amplifier B
				
				(0) undefined
				(1) fault
				(2) ok"
			::= { fmARAmplifierB 2 }

		
		-- 1.3.6.1.4.1.19831.1.1.3.2.3.3
		fmARAmplifierBWarning OBJECT-TYPE
			SYNTAX WarningOK
			MAX-ACCESS read-only
			STATUS current
			DESCRIPTION
				"Active reserve. Warning state of amplifier B
				
				(0) undefined
				(1) warning
				(2) ok"
			::= { fmARAmplifierB 3 }

		
-- fm active reserve excister A
		-- 1.3.6.1.4.1.19831.1.1.3.2.4
		fmARExciterA OBJECT IDENTIFIER ::= { fmActiveReserve 4 }

		
		-- 1.3.6.1.4.1.19831.1.1.3.2.4.1
		fmARExciterALocalMode OBJECT-TYPE
			SYNTAX LocalRemote
			MAX-ACCESS read-only
			STATUS current
			DESCRIPTION
				"Active reserve. State of the local mode
				
				(0) undefined
				(1) local
				(2) remote"
			::= { fmARExciterA 1 }

		
		-- 1.3.6.1.4.1.19831.1.1.3.2.4.2
		fmARExciterAFault OBJECT-TYPE
			SYNTAX FaultOK
			MAX-ACCESS read-only
			STATUS current
			DESCRIPTION
				"Active reserve. State of the exciter A
				
				(0) undefined
				(1) fault
				(2) ok"
			::= { fmARExciterA 2 }

		
		-- 1.3.6.1.4.1.19831.1.1.3.2.4.3
		fmARExciterAWarning OBJECT-TYPE
			SYNTAX WarningOK
			MAX-ACCESS read-only
			STATUS current
			DESCRIPTION
				"Active reserve. Warning state of the exciter A
				
				(0) undefined
				(1) warning
				(2) ok"
			::= { fmARExciterA 3 }

		
-- fm active reserve exciter B
		-- 1.3.6.1.4.1.19831.1.1.3.2.5
		fmARExciterB OBJECT IDENTIFIER ::= { fmActiveReserve 5 }

		
		-- 1.3.6.1.4.1.19831.1.1.3.2.5.1
		fmARExciterBLocalMode OBJECT-TYPE
			SYNTAX LocalRemote
			MAX-ACCESS read-only
			STATUS current
			DESCRIPTION
				"Active reserve. State of the local mode
				
				(0) undefined
				(1) local
				(2) remote"
			::= { fmARExciterB 1 }

		
		-- 1.3.6.1.4.1.19831.1.1.3.2.5.2
		fmARExciterBFault OBJECT-TYPE
			SYNTAX FaultOK
			MAX-ACCESS read-only
			STATUS current
			DESCRIPTION
				"Active reserve. Fault state of the exciter B
				
				(0) undefined
				(1) fault
				(2) ok"
			::= { fmARExciterB 2 }

		
		-- 1.3.6.1.4.1.19831.1.1.3.2.5.3
		fmARExciterBWarning OBJECT-TYPE
			SYNTAX WarningOK
			MAX-ACCESS read-only
			STATUS current
			DESCRIPTION
				"Active reserve. Warning state of the exciter B
				
				(0) undefined
				(1) warning
				(2) ok"
			::= { fmARExciterB 3 }

		
-- fm active reserve event enable
		-- 1.3.6.1.4.1.19831.1.1.3.2.6
		fmAREventEnable OBJECT IDENTIFIER ::= { fmActiveReserve 6 }

		
-- fm active reserve general:  switch for Event
		-- 1.3.6.1.4.1.19831.1.1.3.2.6.1
		fmAREventEnableGeneral OBJECT IDENTIFIER ::= { fmAREventEnable 1 }

		
		-- 1.3.6.1.4.1.19831.1.1.3.2.6.1.1
		fmARPreselectionExciterEnable OBJECT-TYPE
			SYNTAX TruthValue
			MAX-ACCESS read-write
			STATUS current
			DESCRIPTION
				"Description.Enable/Disable switch for fmARPreselectionExciter event"
			::= { fmAREventEnableGeneral 1 }

		
		-- 1.3.6.1.4.1.19831.1.1.3.2.6.1.2
		fmARPreselectionAmplifierEnable OBJECT-TYPE
			SYNTAX TruthValue
			MAX-ACCESS read-write
			STATUS current
			DESCRIPTION
				"Description.Enable/Disable switch for fmARPreselectionAmplifier event"
			::= { fmAREventEnableGeneral 2 }

		
		-- 1.3.6.1.4.1.19831.1.1.3.2.6.1.3
		fmARTransmitterOpModeEnable OBJECT-TYPE
			SYNTAX TruthValue
			MAX-ACCESS read-write
			STATUS current
			DESCRIPTION
				"Description.Enable/Disable switch for fmARTransmitterOpMode event"
			::= { fmAREventEnableGeneral 3 }

		
		-- 1.3.6.1.4.1.19831.1.1.3.2.6.1.4
		fmARReserveControlEnable OBJECT-TYPE
			SYNTAX TruthValue
			MAX-ACCESS read-write
			STATUS current
			DESCRIPTION
				"Description.Enable/Disable switch for fmARReserveControl event"
			::= { fmAREventEnableGeneral 4 }

		
		-- 1.3.6.1.4.1.19831.1.1.3.2.6.1.5
		fmARActiveAmplifierEnable OBJECT-TYPE
			SYNTAX TruthValue
			MAX-ACCESS read-write
			STATUS current
			DESCRIPTION
				"Description.Enable/Disable switch for fmARActiveAmplifier event"
			::= { fmAREventEnableGeneral 5 }

		
		-- 1.3.6.1.4.1.19831.1.1.3.2.6.1.6
		fmARActiveExciterEnable OBJECT-TYPE
			SYNTAX TruthValue
			MAX-ACCESS read-write
			STATUS current
			DESCRIPTION
				"Description.Enable/Disable switch for fmARActiveExciter event"
			::= { fmAREventEnableGeneral 6 }

		
		-- 1.3.6.1.4.1.19831.1.1.3.2.6.1.7
		fmARLocalModeEnable OBJECT-TYPE
			SYNTAX TruthValue
			MAX-ACCESS read-write
			STATUS current
			DESCRIPTION
				"Description.Enable/Disable switch for fmARLocalMode event"
			::= { fmAREventEnableGeneral 7 }

		
		-- 1.3.6.1.4.1.19831.1.1.3.2.6.1.8
		fmARControlUnitFaultEnable OBJECT-TYPE
			SYNTAX TruthValue
			MAX-ACCESS read-write
			STATUS current
			DESCRIPTION
				"Description.Enable/Disable switch for fmARControlUnitFault event"
			::= { fmAREventEnableGeneral 8 }

		
		-- 1.3.6.1.4.1.19831.1.1.3.2.6.1.9
		fmARExciterSwitchOverModeEnable OBJECT-TYPE
			SYNTAX TruthValue
			MAX-ACCESS read-write
			STATUS current
			DESCRIPTION
				"Description.Enable/Disable switch for fmARExciterSwitchOverMode event"
			::= { fmAREventEnableGeneral 9 }

		
		-- 1.3.6.1.4.1.19831.1.1.3.2.6.1.10
		fmARExciterSwitchOverReadyEnable OBJECT-TYPE
			SYNTAX TruthValue
			MAX-ACCESS read-write
			STATUS current
			DESCRIPTION
				"Description.Enable/Disable switch for fmARExciterSwitchOverReady event"
			::= { fmAREventEnableGeneral 10 }

		
		-- 1.3.6.1.4.1.19831.1.1.3.2.6.1.11
		fmARExciterSwitchOverExecutedEnable OBJECT-TYPE
			SYNTAX TruthValue
			MAX-ACCESS read-write
			STATUS current
			DESCRIPTION
				"Description.Enable/Disable switch for fmARExciterSwitchOverExecuted event"
			::= { fmAREventEnableGeneral 11 }

		
		-- 1.3.6.1.4.1.19831.1.1.3.2.6.1.12
		fmARExciterSwitchOverFaultEnable OBJECT-TYPE
			SYNTAX TruthValue
			MAX-ACCESS read-write
			STATUS current
			DESCRIPTION
				"Description.Enable/Disable switch for fmARExciterSwitchOverFault event"
			::= { fmAREventEnableGeneral 12 }

		
		-- 1.3.6.1.4.1.19831.1.1.3.2.6.1.13
		fmARAmplifierSwitchOverModeEnable OBJECT-TYPE
			SYNTAX TruthValue
			MAX-ACCESS read-write
			STATUS current
			DESCRIPTION
				"Description.Enable/Disable switch for fmARAmplifierSwitchOverMode event"
			::= { fmAREventEnableGeneral 13 }

		
		-- 1.3.6.1.4.1.19831.1.1.3.2.6.1.14
		fmARAmplifierSwitchOverReadyEnable OBJECT-TYPE
			SYNTAX TruthValue
			MAX-ACCESS read-write
			STATUS current
			DESCRIPTION
				"Description.Enable/Disable switch for fmARAmplifierSwitchOverReady event"
			::= { fmAREventEnableGeneral 14 }

		
		-- 1.3.6.1.4.1.19831.1.1.3.2.6.1.15
		fmARAmplifierSwitchOverExecutedEnable OBJECT-TYPE
			SYNTAX TruthValue
			MAX-ACCESS read-write
			STATUS current
			DESCRIPTION
				"Description.Enable/Disable switch for  fmARAmplifierSwitchOverExecuted event"
			::= { fmAREventEnableGeneral 15 }

		
		-- 1.3.6.1.4.1.19831.1.1.3.2.6.1.16
		fmARAmplifierSwitchOverFaultEnable OBJECT-TYPE
			SYNTAX TruthValue
			MAX-ACCESS read-write
			STATUS current
			DESCRIPTION
				"Description.Enable/Disable switch for fmARAmplifierSwitchOverFault event"
			::= { fmAREventEnableGeneral 16 }

		
-- fm active reserve amplifier A:  switch for Event
		-- 1.3.6.1.4.1.19831.1.1.3.2.6.2
		fmAREventEnableAmplifierA OBJECT IDENTIFIER ::= { fmAREventEnable 2 }

		
		-- 1.3.6.1.4.1.19831.1.1.3.2.6.2.1
		fmARAmplifierARFPresentEnable OBJECT-TYPE
			SYNTAX TruthValue
			MAX-ACCESS read-write
			STATUS current
			DESCRIPTION
				"Description.Enable/Disable switch for fmARAmplifierARFPresent event"
			::= { fmAREventEnableAmplifierA 1 }

		
		-- 1.3.6.1.4.1.19831.1.1.3.2.6.2.2
		fmARAmplifierAFaultEnable OBJECT-TYPE
			SYNTAX TruthValue
			MAX-ACCESS read-write
			STATUS current
			DESCRIPTION
				"Description.Enable/Disable switch for fmARAmplifierAFault event"
			::= { fmAREventEnableAmplifierA 2 }

		
		-- 1.3.6.1.4.1.19831.1.1.3.2.6.2.3
		fmARAmplifierAWarningEnable OBJECT-TYPE
			SYNTAX TruthValue
			MAX-ACCESS read-write
			STATUS current
			DESCRIPTION
				"Description.Enable/Disable switch for fmARAmplifierAWarning event"
			::= { fmAREventEnableAmplifierA 3 }

		
-- fm active reserve amplifier B:  switch for Event
		-- 1.3.6.1.4.1.19831.1.1.3.2.6.3
		fmAREventEnableAmplifierB OBJECT IDENTIFIER ::= { fmAREventEnable 3 }

		
		-- 1.3.6.1.4.1.19831.1.1.3.2.6.3.1
		fmARAmplifierBRFPresentEnable OBJECT-TYPE
			SYNTAX TruthValue
			MAX-ACCESS read-write
			STATUS current
			DESCRIPTION
				"Description.Enable/Disable switch for fmARAmplifierBRFPresent event"
			::= { fmAREventEnableAmplifierB 1 }

		
		-- 1.3.6.1.4.1.19831.1.1.3.2.6.3.2
		fmARAmplifierBFaultEnable OBJECT-TYPE
			SYNTAX TruthValue
			MAX-ACCESS read-write
			STATUS current
			DESCRIPTION
				"Description.Enable/Disable switch for fmARAmplifierBFault event"
			::= { fmAREventEnableAmplifierB 2 }

		
		-- 1.3.6.1.4.1.19831.1.1.3.2.6.3.3
		fmARAmplifierBWarningEnable OBJECT-TYPE
			SYNTAX TruthValue
			MAX-ACCESS read-write
			STATUS current
			DESCRIPTION
				"Description.Enable/Disable switch for fmARAmplifierBWarning event"
			::= { fmAREventEnableAmplifierB 3 }

		
-- fm active reserve exciter A:  switch for event
		-- 1.3.6.1.4.1.19831.1.1.3.2.6.4
		fmAREventEnableExciterA OBJECT IDENTIFIER ::= { fmAREventEnable 4 }

		
		-- 1.3.6.1.4.1.19831.1.1.3.2.6.4.1
		fmARExciterALocalModeEnable OBJECT-TYPE
			SYNTAX TruthValue
			MAX-ACCESS read-write
			STATUS current
			DESCRIPTION
				"Description.Enable/Disable switch for fmARExciterALocalMode event"
			::= { fmAREventEnableExciterA 1 }

		
		-- 1.3.6.1.4.1.19831.1.1.3.2.6.4.2
		fmARExciterAFaultEnable OBJECT-TYPE
			SYNTAX TruthValue
			MAX-ACCESS read-write
			STATUS current
			DESCRIPTION
				"Description.Enable/Disable switch for fmARExciterAFault event"
			::= { fmAREventEnableExciterA 2 }

		
		-- 1.3.6.1.4.1.19831.1.1.3.2.6.4.3
		fmARExciterAWarningEnable OBJECT-TYPE
			SYNTAX TruthValue
			MAX-ACCESS read-write
			STATUS current
			DESCRIPTION
				"Description.Enable/Disable switch for fmARExciterAWarning event"
			::= { fmAREventEnableExciterA 3 }

		
-- fm active reserve exciter B: switch event
		-- 1.3.6.1.4.1.19831.1.1.3.2.6.5
		fmAREventEnableExciterB OBJECT IDENTIFIER ::= { fmAREventEnable 5 }

		
		-- 1.3.6.1.4.1.19831.1.1.3.2.6.5.1
		mARExciterBLocalModeEnable OBJECT-TYPE
			SYNTAX TruthValue
			MAX-ACCESS read-write
			STATUS current
			DESCRIPTION
				"Description.Enable/Disable switch for fmARExciterBLocalMode event"
			::= { fmAREventEnableExciterB 1 }

		
		-- 1.3.6.1.4.1.19831.1.1.3.2.6.5.2
		fmARExciterBFaultEnable OBJECT-TYPE
			SYNTAX TruthValue
			MAX-ACCESS read-write
			STATUS current
			DESCRIPTION
				"Description.Enable/Disable switch for fmARExciterBFault event"
			::= { fmAREventEnableExciterB 2 }

		
		-- 1.3.6.1.4.1.19831.1.1.3.2.6.5.3
		fmARExciterBWarningEnable OBJECT-TYPE
			SYNTAX TruthValue
			MAX-ACCESS read-write
			STATUS current
			DESCRIPTION
				"Description.Enable/Disable switch for fmARExciterBWarning event"
			::= { fmAREventEnableExciterB 3 }

		
-- fm active reserve event priority
		-- 1.3.6.1.4.1.19831.1.1.3.2.7
		fmAREventPriority OBJECT IDENTIFIER ::= { fmActiveReserve 7 }

		
-- fm active reserve event priority general
		-- 1.3.6.1.4.1.19831.1.1.3.2.7.1
		fmAREventPriorityGeneral OBJECT IDENTIFIER ::= { fmAREventPriority 1 }

		
		-- 1.3.6.1.4.1.19831.1.1.3.2.7.1.1
		fmARPreselectionExciterPriority OBJECT-TYPE
			SYNTAX Unsigned32
			MAX-ACCESS read-write
			STATUS current
			DESCRIPTION
				"Description.Priority for fmARPreselectionExciter event"
			::= { fmAREventPriorityGeneral 1 }

		
		-- 1.3.6.1.4.1.19831.1.1.3.2.7.1.2
		fmARPreselectionAmplifierPriority OBJECT-TYPE
			SYNTAX Unsigned32
			MAX-ACCESS read-write
			STATUS current
			DESCRIPTION
				"Description.Priority for fmARPreselectionAmplifier event"
			::= { fmAREventPriorityGeneral 2 }

		
		-- 1.3.6.1.4.1.19831.1.1.3.2.7.1.3
		fmARTransmitterOpModePriority OBJECT-TYPE
			SYNTAX Unsigned32
			MAX-ACCESS read-write
			STATUS current
			DESCRIPTION
				"Description.Priority for fmARTransmitterOpMode event"
			::= { fmAREventPriorityGeneral 3 }

		
		-- 1.3.6.1.4.1.19831.1.1.3.2.7.1.4
		fmARReserveControlPriority OBJECT-TYPE
			SYNTAX Unsigned32
			MAX-ACCESS read-write
			STATUS current
			DESCRIPTION
				"Description.Priority for fmARReserveControl event"
			::= { fmAREventPriorityGeneral 4 }

		
		-- 1.3.6.1.4.1.19831.1.1.3.2.7.1.5
		fmARActiveAmplifierPriority OBJECT-TYPE
			SYNTAX Unsigned32
			MAX-ACCESS read-write
			STATUS current
			DESCRIPTION
				"Description.Priority for fmARActiveAmplifier event"
			::= { fmAREventPriorityGeneral 5 }

		
		-- 1.3.6.1.4.1.19831.1.1.3.2.7.1.6
		fmARActiveExciterPriority OBJECT-TYPE
			SYNTAX Unsigned32
			MAX-ACCESS read-write
			STATUS current
			DESCRIPTION
				"Description.Priority for fmARActiveExciter event"
			::= { fmAREventPriorityGeneral 6 }

		
		-- 1.3.6.1.4.1.19831.1.1.3.2.7.1.7
		fmARLocalModePriority OBJECT-TYPE
			SYNTAX Unsigned32
			MAX-ACCESS read-write
			STATUS current
			DESCRIPTION
				"Description.Priority for fmARLocalMode event"
			::= { fmAREventPriorityGeneral 7 }

		
		-- 1.3.6.1.4.1.19831.1.1.3.2.7.1.8
		fmARControlUnitFaultPriority OBJECT-TYPE
			SYNTAX Unsigned32
			MAX-ACCESS read-write
			STATUS current
			DESCRIPTION
				"Description.Priority for fmARControlUnitFault event"
			::= { fmAREventPriorityGeneral 8 }

		
		-- 1.3.6.1.4.1.19831.1.1.3.2.7.1.9
		fmARExciterSwitchOverModePriority OBJECT-TYPE
			SYNTAX Unsigned32
			MAX-ACCESS read-write
			STATUS current
			DESCRIPTION
				"Description.Priority for fmARExciterSwitchOverMode event"
			::= { fmAREventPriorityGeneral 9 }

		
		-- 1.3.6.1.4.1.19831.1.1.3.2.7.1.10
		fmARExciterSwitchOverReadyPriority OBJECT-TYPE
			SYNTAX Unsigned32
			MAX-ACCESS read-write
			STATUS current
			DESCRIPTION
				"Description.Priority for fmARExciterSwitchOverReady event"
			::= { fmAREventPriorityGeneral 10 }

		
		-- 1.3.6.1.4.1.19831.1.1.3.2.7.1.11
		fmARExciterSwitchOverExecutedPriority OBJECT-TYPE
			SYNTAX Unsigned32
			MAX-ACCESS read-write
			STATUS current
			DESCRIPTION
				"Description.Priority for fmARExciterSwitchOverExecuted event"
			::= { fmAREventPriorityGeneral 11 }

		
		-- 1.3.6.1.4.1.19831.1.1.3.2.7.1.12
		fmARExciterSwitchOverFaultPriority OBJECT-TYPE
			SYNTAX Unsigned32
			MAX-ACCESS read-write
			STATUS current
			DESCRIPTION
				"Description.Priority for fmARExciterSwitchOverFault event"
			::= { fmAREventPriorityGeneral 12 }

		
		-- 1.3.6.1.4.1.19831.1.1.3.2.7.1.13
		fmARAmplifierSwitchOverModePriority OBJECT-TYPE
			SYNTAX Unsigned32
			MAX-ACCESS read-write
			STATUS current
			DESCRIPTION
				"Description.Priority for fmARAmplifierSwitchOverMode event"
			::= { fmAREventPriorityGeneral 13 }

		
		-- 1.3.6.1.4.1.19831.1.1.3.2.7.1.14
		fmARAmplifierSwitchOverReadyPriority OBJECT-TYPE
			SYNTAX Unsigned32
			MAX-ACCESS read-write
			STATUS current
			DESCRIPTION
				"Description.Priority for fmARAmplifierSwitchOverReady event"
			::= { fmAREventPriorityGeneral 14 }

		
		-- 1.3.6.1.4.1.19831.1.1.3.2.7.1.15
		fmARAmplifierSwitchOverExecutedPriority OBJECT-TYPE
			SYNTAX Unsigned32
			MAX-ACCESS read-write
			STATUS current
			DESCRIPTION
				"Description.Priority for fmARAmplifierSwitchOverExecuted event"
			::= { fmAREventPriorityGeneral 15 }

		
		-- 1.3.6.1.4.1.19831.1.1.3.2.7.1.16
		fmARAmplifierSwitchOverFaultPriority OBJECT-TYPE
			SYNTAX Unsigned32
			MAX-ACCESS read-write
			STATUS current
			DESCRIPTION
				"Description.Priority for fmARAmplifierSwitchOverFault event"
			::= { fmAREventPriorityGeneral 16 }

		
-- fm active reserve  event priority amplifier A
		-- 1.3.6.1.4.1.19831.1.1.3.2.7.2
		fmAREventPriorityAmplifierA OBJECT IDENTIFIER ::= { fmAREventPriority 2 }

		
		-- 1.3.6.1.4.1.19831.1.1.3.2.7.2.1
		fmARAmplifierARFPresentPriority OBJECT-TYPE
			SYNTAX Unsigned32
			MAX-ACCESS read-write
			STATUS current
			DESCRIPTION
				"Description.Priority for fmARAmplifierARFPresent event"
			::= { fmAREventPriorityAmplifierA 1 }

		
		-- 1.3.6.1.4.1.19831.1.1.3.2.7.2.2
		fmARAmplifierAFaultPriority OBJECT-TYPE
			SYNTAX Unsigned32
			MAX-ACCESS read-write
			STATUS current
			DESCRIPTION
				"Description.Priority for fmARAmplifierAFault event"
			::= { fmAREventPriorityAmplifierA 2 }

		
		-- 1.3.6.1.4.1.19831.1.1.3.2.7.2.3
		fmARAmplifierAWarningPriority OBJECT-TYPE
			SYNTAX Unsigned32
			MAX-ACCESS read-write
			STATUS current
			DESCRIPTION
				"Description.Priority for fmARAmplifierAWarning event"
			::= { fmAREventPriorityAmplifierA 3 }

		
-- fm active reserve event priority amplifier B
		-- 1.3.6.1.4.1.19831.1.1.3.2.7.3
		fmAREventPriorityAmplifierB OBJECT IDENTIFIER ::= { fmAREventPriority 3 }

		
		-- 1.3.6.1.4.1.19831.1.1.3.2.7.3.1
		fmARAmplifierBRFPresentPriority OBJECT-TYPE
			SYNTAX Unsigned32
			MAX-ACCESS read-write
			STATUS current
			DESCRIPTION
				"Description.Priority for fmARAmplifierBRFPresent event"
			::= { fmAREventPriorityAmplifierB 1 }

		
		-- 1.3.6.1.4.1.19831.1.1.3.2.7.3.2
		fmARAmplifierBFaultPriority OBJECT-TYPE
			SYNTAX Unsigned32
			MAX-ACCESS read-write
			STATUS current
			DESCRIPTION
				"Description.Priority for fmARAmplifierBFault event"
			::= { fmAREventPriorityAmplifierB 2 }

		
		-- 1.3.6.1.4.1.19831.1.1.3.2.7.3.3
		fmARAmplifierBWarningPriority OBJECT-TYPE
			SYNTAX Unsigned32
			MAX-ACCESS read-write
			STATUS current
			DESCRIPTION
				"Description.Priority for fmARAmplifierBWarning event"
			::= { fmAREventPriorityAmplifierB 3 }

		
-- fm active reserve event priority exciter A
		-- 1.3.6.1.4.1.19831.1.1.3.2.7.4
		fmAREventPriorityExciterA OBJECT IDENTIFIER ::= { fmAREventPriority 4 }

		
		-- 1.3.6.1.4.1.19831.1.1.3.2.7.4.1
		fmARExciterALocalModePriority OBJECT-TYPE
			SYNTAX Unsigned32
			MAX-ACCESS read-write
			STATUS current
			DESCRIPTION
				"Description. Priority for fmARExciterALocalMode event"
			::= { fmAREventPriorityExciterA 1 }

		
		-- 1.3.6.1.4.1.19831.1.1.3.2.7.4.2
		fmARExciterAFaultPriority OBJECT-TYPE
			SYNTAX Unsigned32
			MAX-ACCESS read-write
			STATUS current
			DESCRIPTION
				"Description.Priority for fmARExciterAFault event"
			::= { fmAREventPriorityExciterA 2 }

		
		-- 1.3.6.1.4.1.19831.1.1.3.2.7.4.3
		fmARExciterAWarningPriority OBJECT-TYPE
			SYNTAX Unsigned32
			MAX-ACCESS read-write
			STATUS current
			DESCRIPTION
				"Description.Priority for fmARExciterAWarning event"
			::= { fmAREventPriorityExciterA 3 }

		
-- fm active reserve event priority exciter B
		-- 1.3.6.1.4.1.19831.1.1.3.2.7.5
		fmAREventPriorityExciterB OBJECT IDENTIFIER ::= { fmAREventPriority 5 }

		
		-- 1.3.6.1.4.1.19831.1.1.3.2.7.5.1
		fmARExciterBLocalModePriority OBJECT-TYPE
			SYNTAX Unsigned32
			MAX-ACCESS read-write
			STATUS current
			DESCRIPTION
				"Description. Priority for fmARExciterBLocalMode event"
			::= { fmAREventPriorityExciterB 1 }

		
		-- 1.3.6.1.4.1.19831.1.1.3.2.7.5.2
		fmARExciterBFaultPriority OBJECT-TYPE
			SYNTAX Unsigned32
			MAX-ACCESS read-write
			STATUS current
			DESCRIPTION
				"Description.Priority for fmARExciterBFault event"
			::= { fmAREventPriorityExciterB 2 }

		
		-- 1.3.6.1.4.1.19831.1.1.3.2.7.5.3
		fmARExciterBWarningPriority OBJECT-TYPE
			SYNTAX Unsigned32
			MAX-ACCESS read-write
			STATUS current
			DESCRIPTION
				"Description.Priority for fmARExciterBWarning event"
			::= { fmAREventPriorityExciterB 3 }

		
		-- 1.3.6.1.4.1.19831.1.1.3.2.8
		groupsAR OBJECT IDENTIFIER ::= { fmActiveReserve 8 }

		
		-- 1.3.6.1.4.1.19831.1.1.3.2.8.1
		objectGroupAR OBJECT-GROUP
			OBJECTS { fmARTransmitterOpMode, fmARReserveControl, fmARActiveAmplifier, fmARActiveExciter, fmARLocalMode, 
				fmARControlUnitFault, fmARExciterSwitchOverMode, fmARExciterSwitchOverReady, fmARExciterSwitchOverExecuted, fmARExciterSwitchOverFault, 
				fmARAmplifierSwitchOverMode, fmARAmplifierSwitchOverReady, fmARAmplifierSwitchOverExecuted, fmARAmplifierSwitchOverFault, fmARAmplifierARFPresent, 
				fmARAmplifierAFault, fmARAmplifierAWarning, fmARAmplifierBRFPresent, fmARAmplifierBFault, fmARAmplifierBWarning, 
				fmARExciterAFault, fmARExciterAWarning, fmARExciterBFault, fmARExciterBWarning, fmARPreselectionExciterEnable, 
				fmARTransmitterOpModeEnable, fmARReserveControlEnable, fmARActiveAmplifierEnable, fmARActiveExciterEnable, fmARLocalModeEnable, 
				fmARControlUnitFaultEnable, fmARExciterSwitchOverModeEnable, fmARExciterSwitchOverExecutedEnable, fmARExciterSwitchOverFaultEnable, fmARAmplifierSwitchOverModeEnable, 
				fmARAmplifierSwitchOverReadyEnable, fmARAmplifierSwitchOverExecutedEnable, fmARAmplifierSwitchOverFaultEnable, fmARExciterSwitchOverReadyEnable, fmARAmplifierARFPresentEnable, 
				fmARAmplifierAFaultEnable, fmARAmplifierAWarningEnable, fmARAmplifierBRFPresentEnable, fmARAmplifierBFaultEnable, fmARAmplifierBWarningEnable, 
				fmARExciterAFaultEnable, fmARExciterAWarningEnable, fmARExciterBFaultEnable, fmARExciterBWarningEnable, fmARTransmitterOpModePriority, 
				fmARReserveControlPriority, fmARActiveAmplifierPriority, fmARActiveExciterPriority, fmARLocalModePriority, fmARControlUnitFaultPriority, 
				fmARExciterSwitchOverModePriority, fmARExciterSwitchOverExecutedPriority, fmARExciterSwitchOverFaultPriority, fmARAmplifierSwitchOverModePriority, fmARAmplifierSwitchOverReadyPriority, 
				fmARAmplifierSwitchOverExecutedPriority, fmARAmplifierSwitchOverFaultPriority, fmARAmplifierARFPresentPriority, fmARAmplifierAFaultPriority, fmARAmplifierAWarningPriority, 
				fmARAmplifierBRFPresentPriority, fmARAmplifierBFaultPriority, fmARAmplifierBWarningPriority, fmARExciterAFaultPriority, fmARExciterAWarningPriority, 
				fmARExciterBFaultPriority, fmARExciterBWarningPriority, fmARPreselectionAmplifier, fmARPreselectionAmplifierPriority, fmARPreselectionAmplifierEnable, 
				fmARExciterALocalModePriority, fmARExciterBLocalModePriority, fmARExciterSwitchOverReadyPriority, fmARPreselectionExciter, fmARExciterALocalMode, 
				fmARExciterBLocalMode, fmARExciterALocalModeEnable, mARExciterBLocalModeEnable, fmARPreselectionExciterPriority }
			STATUS current
			DESCRIPTION 
				"Description. active reserve: object group"
			::= { groupsAR 1 }

		
		-- 1.3.6.1.4.1.19831.1.1.3.2.8.2
		eventGroupAR NOTIFICATION-GROUP
			NOTIFICATIONS { fmARTransmitterOpModeEvent, fmARReserveControlEvent, fmARActiveAmplifierEvent, fmARActiveExciterEvent, fmARLocalModeEvent, 
				fmARControlUnitFaultEvent, fmARExciterSwitchOverModeEvent, fmARExciterSwitchOverReadyEvent, fmARExciterSwitchOverExecutedEvent, fmARExciterSwitchOverFaultEvent, 
				fmARAmplifierSwitchOverModeEvent, fmARAmplifierSwitchOverReadyEvent, fmARAmplifierSwitchOverExecutedEvent, fmARAmplifierSwitchOverFaultEvent, fmARAmplifierARFPresentEvent, 
				fmARAmplifierAFaultEvent, fmARAmplifierAWarningEvent, fmARAmplifierBRFPresentEvent, fmARAmplifierBFaultEvent, fmARAmplifierBWarningEvent, 
				fmARExciterAFaultEvent, fmARExciterAWarningEvent, fmARExciterBFaultEvent, fmARExciterALocalModeEvent, fmARExciterBLocalModeEvent, 
				fmARPreselectionAmplifierEvent, fmARExciterBWarningEvent, fmARPreselectionExciterEvent }
			STATUS current
			DESCRIPTION 
				"Description. events"
			::= { groupsAR 2 }

		
		-- 1.3.6.1.4.1.19831.1.1.3.2.9
		complianceAR OBJECT IDENTIFIER ::= { fmActiveReserve 9 }

		
		-- 1.3.6.1.4.1.19831.1.1.3.2.9.1
		fmActiveReserveCompliance MODULE-COMPLIANCE
			STATUS current
			DESCRIPTION 
				"Compliance Statement"
			MODULE -- this module
				MANDATORY-GROUPS { objectGroupAR, eventGroupAR }
			::= { complianceAR 1 }

		
	
	END

--
-- IRT-FM-ACTIVERESERVE-MIB.my
--
