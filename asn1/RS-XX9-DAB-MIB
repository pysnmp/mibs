--
-- RS-XX9-DAB-MIB.mi2
-- MIB generated by MG-SOFT Visual MIB Builder 2010 Version 8.0  Build 403
-- Wednesday, March 23, 2016 at 08:57:47
--

-- *****************************************************************************
-- *****************************************************************************
-- **
-- **  COPYRIGHT      (c) 2013 Rohde & Schwarz GmbH & Co. KG
-- **                          Muehldorfstrasse 15
-- **    R & S                 D-81671 Muenchen
-- **
-- *****************************************************************************
-- **
-- **  MODULE         RS-XX9-DAB-MIB
-- **  
-- *****************************************************************************
-- *****************************************************************************

    RS-XX9-DAB-MIB DEFINITIONS ::= BEGIN
 
        IMPORTS
            InetAddressType, InetAddress            
                FROM INET-ADDRESS-MIB            
            commonNotificationAlarmClass            
                FROM RS-XX9-COMMON-MIB            
            rsXx9Dab, rsXx9MibModule            
                FROM RS-XX9-SMI-MIB            
            IndexTransmitter, IndexAB, NotificationMask, NotificationPriority, NotificationState            
                FROM RS-XX9-TC-MIB            
            OBJECT-GROUP, MODULE-COMPLIANCE, NOTIFICATION-GROUP            
                FROM SNMPv2-CONF            
            Unsigned32, OBJECT-TYPE, MODULE-IDENTITY, NOTIFICATION-TYPE            
                FROM SNMPv2-SMI            
            TruthValue, TEXTUAL-CONVENTION            
                FROM SNMPv2-TC;
    
    
        rsXx9DabMibModule MODULE-IDENTITY 
            LAST-UPDATED "201603230900Z"		-- March 23, 2016 at 09:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines DAB specific objects
                of XX9000 transmitting systems from Rohde & Schwarz.
                
                The following MIBs are related to this:
                - RS-COMMON-MIB         - mandatory for this MIB
                - RS-XX9-SMI-MIB        - mandatory for this MIB
                - RS-XX9-TC-MIB         - mandatory for this MIB
                - RS-XX9-COMMON-MIB     - mandatory for this MIB"
            REVISION "201603230900Z"		-- March 23, 2016 at 09:00 GMT
            DESCRIPTION 
                "rename dabInputEdiSyncState enum: from etiLi(9) to etiNi(9)"
            REVISION "201511301500Z"		-- November 30, 2015 at 15:00 GMT
            DESCRIPTION 
                "add dabInputEdiTable, dabInputCmnEdiDejitterBuffer, dabInputCmnEdiMaxReplacement, dabInpIfEdiState
                
                "
            REVISION "201502271500Z"		-- February 27, 2015 at 15:00 GMT
            DESCRIPTION 
                "updated description texts"
            REVISION "201502021800Z"		-- February 02, 2015 at 18:00 GMT
            DESCRIPTION 
                "added dabTestRsEnsembleDataChannel, dabTestRsEnsemblePrbs"
            REVISION "201412221600Z"		-- December 22, 2014 at 16:00 GMT
            DESCRIPTION 
                "updated description texts
                "
            REVISION "201409301300Z"		-- September 30, 2014 at 13:00 GMT
            DESCRIPTION 
                "added dabStSfnNetworkCompensationDelayState
                added dabStSfnMfnOverallSignalDelay
                extend range of dabStSfnTistState
                "
            REVISION "201406031200Z"		-- June 03, 2014 at 12:00 GMT
            DESCRIPTION 
                "removed off from dabSetupSfnTistSource's value range
                added dabInpIfEtiState
                added dabInputNotificationTable"
            REVISION "201405161500Z"		-- May 16, 2014 at 15:00 GMT
            DESCRIPTION 
                "added dabTest and dabEncoderSummary notifications
                added dabSetupSfnTxOffsetDelaySource"
            REVISION "201403061600Z"		-- March 06, 2014 at 16:00 GMT
            DESCRIPTION 
                "added dabTiiCarrierPhase"
            REVISION "201312201000Z"		-- December 20, 2013 at 10:00 GMT
            DESCRIPTION 
                "third revision with following changes:
                - change range of dabTiiSubId to 1..23"
            REVISION "201310101400Z"		-- October 10, 2013 at 14:00 GMT
            DESCRIPTION 
                "third revision with following changes:
                - added dabInputEtiErrorLevelState"
            REVISION "201310011000Z"		-- October 01, 2013 at 10:00 GMT
            DESCRIPTION 
                "second revision with following changes:
                - updated value and description of dabInputEtiSyncState (is named na5376 instead of na5372)
                - added dabStatusSfnInputTable with Tist state"
            REVISION "201303131000Z"		-- March 13, 2013 at 10:00 GMT
            DESCRIPTION 
                "Preliminary version."
            ::= { rsXx9MibModule 1 }

        
    
--
-- Textual conventions
--
    
        DabTiiSource ::= TEXTUAL-CONVENTION
            STATUS current
            DESCRIPTION 
                "Behaviour of TII (transmitter identification information).
                off(1)     - not signalled - main ID out of range
                manual(2)  - signalled from manual input
                etiMNSC(3) - signalled from ASS type 0 message"
            SYNTAX INTEGER
                {
                off(1),
                manual(2),
                etiMNSC(3)
                }

        DabMode ::= TEXTUAL-CONVENTION
            STATUS current
            DESCRIPTION 
                "DAB mode"
            SYNTAX INTEGER
                {
                modeI(1),
                modeII(2),
                modeIII(3),
                modeIV(4)
                }

        DabModeSource ::= TEXTUAL-CONVENTION
            STATUS current
            DESCRIPTION 
                "Source for DAB mode:
                manual(1) - from dabModulationMode
                etiMID(2) - signalled by ETI(LI)-MID"
            SYNTAX INTEGER
                {
                manual(1),
                etiMID(2)
                }

        NetworkCompensationDelay ::= TEXTUAL-CONVENTION
            STATUS current
            DESCRIPTION 
                "Description."
            SYNTAX Unsigned32 (0..1000000)

        ErrorLevelState ::= TEXTUAL-CONVENTION
            STATUS current
            DESCRIPTION 
                "Description."
            SYNTAX INTEGER
                {
                undefined(1),
                off(2),
                noSignal(3),
                tooHigh(4),
                ok(5)
                }

        DatarateState ::= TEXTUAL-CONVENTION
            STATUS current
            DESCRIPTION 
                "Description."
            SYNTAX INTEGER
                {
                undefined(1),
                off(2),
                bufferUnderrun(3),
                bufferOverflow(4),
                ok(5)
                }

    
--
-- Node definitions
--
    
        rsXx9DabNotifications OBJECT IDENTIFIER ::= { rsXx9Dab 0 }

        
        dabTiiMainIdOutOfRange NOTIFICATION-TYPE
            OBJECTS { commonNotificationAlarmClass, dabStatusNotificationPriority, dabStatusNotificationState }
            STATUS current
            DESCRIPTION 
                "Indicates that the set TII Main Id is not allowed to use. 
                This warning might occur when the DAB-mode is 
                switched to Mode3. Please check the setting for DAB 
                main-ID.
                
                Possible values:
                off(2)
                warning(4) - Active main ID not admissible in active DAB mode.
                
                Notification class: warning"
            ::= { rsXx9DabNotifications 1 }

        
        dabEncoderSummary NOTIFICATION-TYPE
            OBJECTS { commonNotificationAlarmClass, dabStatusNotificationPriority, dabStatusNotificationState }
            STATUS current
            DESCRIPTION 
                "Encoder summary state.
                
                Possible values:
                off(2)
                fault(3)
                warning(4)
                ok(5)
                
                Notification class: fault"
            ::= { rsXx9DabNotifications 2 }

        
        dabTest NOTIFICATION-TYPE
            OBJECTS { commonNotificationAlarmClass, dabStatusNotificationPriority, dabStatusNotificationState }
            STATUS current
            DESCRIPTION 
                "One of the test signals is activated. 
                If a test signal is activated, decoding 
                of the transmitted signal by the 
                transmitter will not be possible.
                
                Possible values:
                off(2)     - no test signal generation
                warning(4) - test signal generation is activated
                
                Notification class: warning
                "
            ::= { rsXx9DabNotifications 3 }

        
        dabInpIfEtiState NOTIFICATION-TYPE
            OBJECTS { commonNotificationAlarmClass, dabInputNotificationPriority, dabInputNotificationState }
            STATUS current
            DESCRIPTION 
                "Description."
            ::= { rsXx9DabNotifications 4 }

        
        dabInpIfEdiState NOTIFICATION-TYPE
            OBJECTS { commonNotificationAlarmClass, dabInputNotificationPriority, dabInputNotificationState }
            STATUS current
            DESCRIPTION 
                "Description."
            ::= { rsXx9DabNotifications 5 }

        
        rsXx9DabObjects OBJECT IDENTIFIER ::= { rsXx9Dab 1 }

        
        dabInput OBJECT IDENTIFIER ::= { rsXx9DabObjects 1 }

        
        dabInputCommonTable OBJECT-TYPE
            SYNTAX SEQUENCE OF DabInputCommonEntry
            MAX-ACCESS not-accessible
            STATUS current
            DESCRIPTION
                "Common parameters for all inputs."
            ::= { dabInput 1 }

        
        dabInputCommonEntry OBJECT-TYPE
            SYNTAX DabInputCommonEntry
            MAX-ACCESS not-accessible
            STATUS current
            DESCRIPTION
                "An entry in the dabInputCommonTable."
            INDEX { dabInputCmnTxIdx, dabInputCmnExcIdx }
            ::= { dabInputCommonTable 1 }

        
        DabInputCommonEntry ::=
            SEQUENCE { 
                dabInputCmnTxIdx
                    IndexTransmitter,
                dabInputCmnExcIdx
                    IndexAB,
                dabInputCmnImpedance
                    INTEGER,
                dabInputCmnEdiDejitterBuffer
                    Unsigned32,
                dabInputCmnEdiMaxReplacements
                    Unsigned32
             }

        dabInputCmnTxIdx OBJECT-TYPE
            SYNTAX IndexTransmitter
            MAX-ACCESS not-accessible
            STATUS current
            DESCRIPTION
                "The transmitter index."
            ::= { dabInputCommonEntry 1 }

        
        dabInputCmnExcIdx OBJECT-TYPE
            SYNTAX IndexAB
            MAX-ACCESS not-accessible
            STATUS current
            DESCRIPTION
                "This index distinguishes the exiters.
                Necessary if you have dual drive transmitters."
            ::= { dabInputCommonEntry 2 }

        
        dabInputCmnImpedance OBJECT-TYPE
            SYNTAX INTEGER
                {
                ohm75(2),
                high(3)
                }
            MAX-ACCESS read-write
            STATUS current
            DESCRIPTION
                "Description."
            ::= { dabInputCommonEntry 3 }

        
        dabInputCmnEdiDejitterBuffer OBJECT-TYPE
            SYNTAX Unsigned32 (10..100)
            UNITS "frames"
            MAX-ACCESS read-write
            STATUS current
            DESCRIPTION
                "Determines the buffer time at start, before the input data is forwarded to EDI handling. 
                This value should be greater than the expected jitter of the input network. 
                "
            ::= { dabInputCommonEntry 4 }

        
        dabInputCmnEdiMaxReplacements OBJECT-TYPE
            SYNTAX Unsigned32 (0..255)
            UNITS "frames"
            MAX-ACCESS read-write
            STATUS current
            DESCRIPTION
                "Determines the number of ETI frames, which can be created because of replacement. 
                If this number is exceeded, the input is switched off. 
                "
            ::= { dabInputCommonEntry 5 }

        
        dabInputEtiTable OBJECT-TYPE
            SYNTAX SEQUENCE OF DabInputEtiEntry
            MAX-ACCESS not-accessible
            STATUS current
            DESCRIPTION
                "ETI input parameters."
            ::= { dabInput 2 }

        
        dabInputEtiEntry OBJECT-TYPE
            SYNTAX DabInputEtiEntry
            MAX-ACCESS not-accessible
            STATUS current
            DESCRIPTION
                "An entry in the dabInputEtiTable."
            INDEX { dabInputCmnTxIdx, dabInputCmnExcIdx, dabInputEtiInputIdx }
            ::= { dabInputEtiTable 1 }

        
        DabInputEtiEntry ::=
            SEQUENCE { 
                dabInputEtiInputIdx
                    INTEGER,
                dabInputEtiSyncState
                    INTEGER,
                dabInputEtiDatarate
                    Unsigned32,
                dabInputEtiDatarateState
                    DatarateState,
                dabInputEtiErrorLevelState
                    ErrorLevelState
             }

        dabInputEtiInputIdx OBJECT-TYPE
            SYNTAX INTEGER
                {
                input1(1),
                input2(2)
                }
            MAX-ACCESS not-accessible
            STATUS current
            DESCRIPTION
                "Input index."
            ::= { dabInputEtiEntry 1 }

        
        dabInputEtiSyncState OBJECT-TYPE
            SYNTAX INTEGER
                {
                undefined(1),
                noSignal(2),
                ais(3),
                g703(4),
                g704(5),
                niG703(6),
                na5592(7),
                na5376(8)
                }
            MAX-ACCESS read-only
            STATUS current
            DESCRIPTION
                "Indicates whether the synchronisation could occur on the data stream and which 
                kind of feeding the data stream is used.
                
                niG703(6) - ETI(NI, G.703)
                na5592(7) - ETI(NA, G.704)5592
                na5376(8) - ETI(NA, G.704)5376"
            ::= { dabInputEtiEntry 2 }

        
        dabInputEtiDatarate OBJECT-TYPE
            SYNTAX Unsigned32
            UNITS "bits per second"
            MAX-ACCESS read-only
            STATUS current
            DESCRIPTION
                "The total data rate inclusive stuffing bytes at ETI feed."
            ::= { dabInputEtiEntry 3 }

        
        dabInputEtiDatarateState OBJECT-TYPE
            SYNTAX DatarateState
            MAX-ACCESS read-only
            STATUS current
            DESCRIPTION
                "Description."
            ::= { dabInputEtiEntry 4 }

        
        dabInputEtiErrorLevelState OBJECT-TYPE
            SYNTAX ErrorLevelState
            MAX-ACCESS read-only
            STATUS current
            DESCRIPTION
                "Indicates the status of error level included in the ETI. The status 
                is set from a multiplexer individually for each ETI Frame. 
                
                Off: The monitoring is deactivated. 
                No Signal: No signal is being applied. 
                Too High: The error level is  2. This input is used no longer. 
                Ok: The error level is 2.
                "
            ::= { dabInputEtiEntry 5 }

        
        dabInputNotificationTable OBJECT-TYPE
            SYNTAX SEQUENCE OF DabInputNotificationEntry
            MAX-ACCESS not-accessible
            STATUS current
            DESCRIPTION
                "The context information/configuration for the
                DAB input notifications."
            ::= { dabInput 3 }

        
        dabInputNotificationEntry OBJECT-TYPE
            SYNTAX DabInputNotificationEntry
            MAX-ACCESS not-accessible
            STATUS current
            DESCRIPTION
                "Description."
            INDEX { dabInputNotificationTxIdx, dabInputNotificationExcIdx, dabInputNotificationInputIdx, dabInputNotificationIdx }
            ::= { dabInputNotificationTable 1 }

        
        DabInputNotificationEntry ::=
            SEQUENCE { 
                dabInputNotificationTxIdx
                    IndexTransmitter,
                dabInputNotificationExcIdx
                    IndexAB,
                dabInputNotificationInputIdx
                    INTEGER,
                dabInputNotificationIdx
                    Unsigned32,
                dabInputNotificationName
                    INTEGER,
                dabInputNotificationMask
                    NotificationMask,
                dabInputNotificationPriority
                    NotificationPriority,
                dabInputNotificationState
                    NotificationState
             }

        dabInputNotificationTxIdx OBJECT-TYPE
            SYNTAX IndexTransmitter
            MAX-ACCESS not-accessible
            STATUS current
            DESCRIPTION
                "The transmitter index."
            ::= { dabInputNotificationEntry 1 }

        
        dabInputNotificationExcIdx OBJECT-TYPE
            SYNTAX IndexAB
            MAX-ACCESS not-accessible
            STATUS current
            DESCRIPTION
                "This index distinguishes the exiters.
                Necessary if you have dual drive transmitters."
            ::= { dabInputNotificationEntry 2 }

        
        dabInputNotificationInputIdx OBJECT-TYPE
            SYNTAX INTEGER
                {
                input1(1),
                input2(2)
                }
            MAX-ACCESS not-accessible
            STATUS current
            DESCRIPTION
                "Input index."
            ::= { dabInputNotificationEntry 3 }

        
        dabInputNotificationIdx OBJECT-TYPE
            SYNTAX Unsigned32 (4..5)
            MAX-ACCESS not-accessible
            STATUS current
            DESCRIPTION
                "The notification number as below rsXx9DabNotifications.
                This is a helper column and therefore not-accessible."
            ::= { dabInputNotificationEntry 4 }

        
        dabInputNotificationName OBJECT-TYPE
            SYNTAX INTEGER
                {
                dabInpIfEtiState(4),
                dabInpIfEdiState(5)
                }
            MAX-ACCESS read-only
            STATUS current
            DESCRIPTION
                "The notification number as an enumeration.
                The enumeration correlates with the notifications below rsXx9DabNotifications."
            ::= { dabInputNotificationEntry 5 }

        
        dabInputNotificationMask OBJECT-TYPE
            SYNTAX NotificationMask
            MAX-ACCESS read-write
            STATUS current
            DESCRIPTION
                "See textual convention for details."
            ::= { dabInputNotificationEntry 6 }

        
        dabInputNotificationPriority OBJECT-TYPE
            SYNTAX NotificationPriority
            MAX-ACCESS read-write
            STATUS current
            DESCRIPTION
                "See textual convention for details."
            ::= { dabInputNotificationEntry 7 }

        
        dabInputNotificationState OBJECT-TYPE
            SYNTAX NotificationState
            MAX-ACCESS read-only
            STATUS current
            DESCRIPTION
                "See textual convention for details."
            ::= { dabInputNotificationEntry 8 }

        
        dabInputEdiTable OBJECT-TYPE
            SYNTAX SEQUENCE OF DabInputEdiEntry
            MAX-ACCESS not-accessible
            STATUS current
            DESCRIPTION
                "EDI input parameters."
            ::= { dabInput 4 }

        
        dabInputEdiEntry OBJECT-TYPE
            SYNTAX DabInputEdiEntry
            MAX-ACCESS not-accessible
            STATUS current
            DESCRIPTION
                "An entry in the dabInputEdiTable."
            INDEX { dabInputCmnTxIdx, dabInputCmnExcIdx, dabInputNotificationInputIdx }
            ::= { dabInputEdiTable 1 }

        
        DabInputEdiEntry ::=
            SEQUENCE { 
                dabInputEdiSyncState
                    INTEGER,
                dabInputEdiDatarate
                    Unsigned32,
                dabInputEdiDatarateState
                    DatarateState,
                dabInputEdiConnector
                    INTEGER,
                dabInputEdiStreamingMode
                    INTEGER,
                dabInputEdiStreamAddressType
                    InetAddressType,
                dabInputEdiStreamAddress
                    InetAddress,
                dabInputEdiStreamPort
                    Unsigned32,
                dabInputEdiErrorLevelState
                    ErrorLevelState,
                dabInputEdiReplacementStatus
                    INTEGER,
                dabInputEdiFecMode
                    INTEGER
             }

        dabInputEdiSyncState OBJECT-TYPE
            SYNTAX INTEGER
                {
                undefined(0),
                noSignal(1),
                stiDLi(8),
                etiNi(9)
                }
            MAX-ACCESS read-only
            STATUS current
            DESCRIPTION
                "Indicates whether the datastream could be synchronized 
                and which type of the datastream is fed.
                "
            ::= { dabInputEdiEntry 1 }

        
        dabInputEdiDatarate OBJECT-TYPE
            SYNTAX Unsigned32
            UNITS "bits per second"
            MAX-ACCESS read-only
            STATUS current
            DESCRIPTION
                "Indicates the total data rate (gross data rate) on the EDI feed.
                "
            ::= { dabInputEdiEntry 2 }

        
        dabInputEdiDatarateState OBJECT-TYPE
            SYNTAX DatarateState
            MAX-ACCESS read-only
            STATUS current
            DESCRIPTION
                "Description."
            ::= { dabInputEdiEntry 3 }

        
        dabInputEdiConnector OBJECT-TYPE
            SYNTAX INTEGER
                {
                tsLan1(1),
                tsLan2(2)
                }
            MAX-ACCESS read-write
            STATUS current
            DESCRIPTION
                "Used to define the physical network interface to which the logical EDI stream 
                 is bound. Normally, the TS LAN 1 socket (X30) is coupled to EDI stream 1 and 
                 the TS LAN 2 socket (X31) to EDI stream 2. This allows you to use multiple 
                 redundant servers that can be selected automatically using the automatic 
                 input signal switchover. However, it is also possible to feed several 
                 multicast streams via the same physical Ethernet socket. In this case, too, 
                 the automatic input signal switchover function can toggle automatically 
                 between two data streams."
            ::= { dabInputEdiEntry 4 }

        
        dabInputEdiStreamingMode OBJECT-TYPE
            SYNTAX INTEGER
                {
                uniCast(1),
                multiCast(2)
                }
            MAX-ACCESS read-write
            STATUS current
            DESCRIPTION
                "Determines the streaming mode. "
            ::= { dabInputEdiEntry 5 }

        
        dabInputEdiStreamAddressType OBJECT-TYPE
            SYNTAX InetAddressType
            MAX-ACCESS read-only
            STATUS current
            DESCRIPTION
                "Description."
            ::= { dabInputEdiEntry 6 }

        
        dabInputEdiStreamAddress OBJECT-TYPE
            SYNTAX InetAddress
            MAX-ACCESS read-write
            STATUS current
            DESCRIPTION
                "If dabInputEdiStreamingMode is unicast(1) this object is read-only and shows the IP address
                 on the physical connector.
                 If dabInputEdiStreamingMode is multicast(2) this object is read-write for configuration
                 of the multicast source the IP address.
                "
            ::= { dabInputEdiEntry 7 }

        
        dabInputEdiStreamPort OBJECT-TYPE
            SYNTAX Unsigned32 (1..65535)
            MAX-ACCESS read-write
            STATUS current
            DESCRIPTION
                "The port of the logical input stream. "
            ::= { dabInputEdiEntry 8 }

        
        dabInputEdiErrorLevelState OBJECT-TYPE
            SYNTAX ErrorLevelState
            MAX-ACCESS read-only
            STATUS current
            DESCRIPTION
                "Indicates the status of error level included in the EDI. The status 
                is set from a multiplexer individually for each EDI Frame. 
                
                Off: The monitoring is deactivated. 
                No Signal: No signal is being applied. 
                Too High: The error level is  2. This input is used no longer. 
                Ok: The error level is 2.
                "
            ::= { dabInputEdiEntry 9 }

        
        dabInputEdiReplacementStatus OBJECT-TYPE
            SYNTAX INTEGER
                {
                undefined(1),
                noInput(2),
                unused(3),
                replacedFrames(4),
                ok(5)
                }
            MAX-ACCESS read-write
            STATUS current
            DESCRIPTION
                "Description."
            ::= { dabInputEdiEntry 10 }

        
        dabInputEdiFecMode OBJECT-TYPE
            SYNTAX INTEGER
                {
                undefined(1),
                off(2),
                mode1(3),
                mode2(4),
                mode3(5),
                mode4(6),
                mode5(7),
                mode6OrHigher(8),
                unknown(9)
                }
            MAX-ACCESS read-only
            STATUS current
            DESCRIPTION
                "Shows the fed FEC."
            ::= { dabInputEdiEntry 11 }

        
        dabStatus OBJECT IDENTIFIER ::= { rsXx9DabObjects 2 }

        
        dabStatusNotificationTable OBJECT-TYPE
            SYNTAX SEQUENCE OF DabStatusNotificationEntry
            MAX-ACCESS not-accessible
            STATUS current
            DESCRIPTION
                "The context information/configuration for the
                DAB status notifications."
            ::= { dabStatus 1 }

        
        dabStatusNotificationEntry OBJECT-TYPE
            SYNTAX DabStatusNotificationEntry
            MAX-ACCESS not-accessible
            STATUS current
            DESCRIPTION
                "An entry in the dabStatusNotificationTable."
            INDEX { dabStatusNotificationTxIdx, dabStatusNotificationExcIdx, dabStatusNotificationIdx }
            ::= { dabStatusNotificationTable 1 }

        
        DabStatusNotificationEntry ::=
            SEQUENCE { 
                dabStatusNotificationTxIdx
                    IndexTransmitter,
                dabStatusNotificationExcIdx
                    IndexAB,
                dabStatusNotificationIdx
                    Unsigned32,
                dabStatusNotificationName
                    INTEGER,
                dabStatusNotificationMask
                    NotificationMask,
                dabStatusNotificationPriority
                    NotificationPriority,
                dabStatusNotificationState
                    NotificationState
             }

        dabStatusNotificationTxIdx OBJECT-TYPE
            SYNTAX IndexTransmitter
            MAX-ACCESS not-accessible
            STATUS current
            DESCRIPTION
                "The transmitter index."
            ::= { dabStatusNotificationEntry 1 }

        
        dabStatusNotificationExcIdx OBJECT-TYPE
            SYNTAX IndexAB
            MAX-ACCESS not-accessible
            STATUS current
            DESCRIPTION
                "This index distinguishes the exiters.
                Necessary if you have dual drive transmitters."
            ::= { dabStatusNotificationEntry 2 }

        
        dabStatusNotificationIdx OBJECT-TYPE
            SYNTAX Unsigned32 (1..3)
            MAX-ACCESS not-accessible
            STATUS current
            DESCRIPTION
                "The notification number as below rsXx9DabNotifications.
                This is a helper column and therefore not-accessible."
            ::= { dabStatusNotificationEntry 3 }

        
        dabStatusNotificationName OBJECT-TYPE
            SYNTAX INTEGER
                {
                dabTiiMainIdOutOfRange(1),
                dabEncoderSummary(2),
                dabTest(3)
                }
            MAX-ACCESS read-only
            STATUS current
            DESCRIPTION
                "The notification number as an enumeration.
                The enumeration correlates with the notifications below rsXx9DabNotifications."
            ::= { dabStatusNotificationEntry 4 }

        
        dabStatusNotificationMask OBJECT-TYPE
            SYNTAX NotificationMask
            MAX-ACCESS read-write
            STATUS current
            DESCRIPTION
                "See textual convention for details."
            ::= { dabStatusNotificationEntry 5 }

        
        dabStatusNotificationPriority OBJECT-TYPE
            SYNTAX NotificationPriority
            MAX-ACCESS read-write
            STATUS current
            DESCRIPTION
                "See textual convention for details."
            ::= { dabStatusNotificationEntry 6 }

        
        dabStatusNotificationState OBJECT-TYPE
            SYNTAX NotificationState
            MAX-ACCESS read-only
            STATUS current
            DESCRIPTION
                "See textual convention for details."
            ::= { dabStatusNotificationEntry 7 }

        
        dabActiveConfigurationTable OBJECT-TYPE
            SYNTAX SEQUENCE OF DabActiveConfigurationEntry
            MAX-ACCESS not-accessible
            STATUS current
            DESCRIPTION
                "Current general DAB configuration."
            ::= { dabStatus 2 }

        
        dabActiveConfigurationEntry OBJECT-TYPE
            SYNTAX DabActiveConfigurationEntry
            MAX-ACCESS not-accessible
            STATUS current
            DESCRIPTION
                "An entry in the dabActiveConfigurationTable."
            INDEX { dabStatusNotificationTxIdx, dabStatusNotificationExcIdx }
            ::= { dabActiveConfigurationTable 1 }

        
        DabActiveConfigurationEntry ::=
            SEQUENCE { 
                dabActCfgModeSource
                    DabModeSource
             }

        dabActCfgModeSource OBJECT-TYPE
            SYNTAX DabModeSource
            MAX-ACCESS read-only
            STATUS current
            DESCRIPTION
                "Indicates the source from which the DAB mode setting is retrieved. 
                
                Manual: DAB mode is set manually at the transmitter. 
                ETI (LI)-MID: DAB mode is read out from the ETI header.
                "
            ::= { dabActiveConfigurationEntry 1 }

        
        dabActiveLocalizationTable OBJECT-TYPE
            SYNTAX SEQUENCE OF DabActiveLocalizationEntry
            MAX-ACCESS not-accessible
            STATUS current
            DESCRIPTION
                "Current DAB localization parameters."
            ::= { dabStatus 3 }

        
        dabActiveLocalizationEntry OBJECT-TYPE
            SYNTAX DabActiveLocalizationEntry
            MAX-ACCESS not-accessible
            STATUS current
            DESCRIPTION
                "An entry in the dabActiveLocalizationTable."
            INDEX { dabStatusNotificationTxIdx, dabStatusNotificationExcIdx }
            ::= { dabActiveLocalizationTable 1 }

        
        DabActiveLocalizationEntry ::=
            SEQUENCE { 
                dabActLclTxAddressPresentPlain
                    TruthValue,
                dabActLclTxAddressRequired
                    TruthValue,
                dabActLclTxAddressState
                    INTEGER,
                dabActLclTiiSource
                    DabTiiSource
             }

        dabActLclTxAddressPresentPlain OBJECT-TYPE
            SYNTAX TruthValue
            MAX-ACCESS read-only
            STATUS current
            DESCRIPTION
                "Indicates whether transmitter identification information (TII) 
                for the set transmitter address is contained in the transport 
                stream.
                "
            ::= { dabActiveLocalizationEntry 1 }

        
        dabActLclTxAddressRequired OBJECT-TYPE
            SYNTAX TruthValue
            MAX-ACCESS read-only
            STATUS current
            DESCRIPTION
                "Depending on the setting for TII Source, indicates whether the Tx address is evaluated."
            ::= { dabActiveLocalizationEntry 2 }

        
        dabActLclTxAddressState OBJECT-TYPE
            SYNTAX INTEGER
                {
                undefined(1),
                neverSeen(2),
                holdover(3),
                ok(4)
                }
            MAX-ACCESS read-only
            STATUS current
            DESCRIPTION
                "Indicates whether the Tx address is present. 
                
                Never Seen: No Tx address has been found in the data stream. 
                The main ID is set to 0 and the sub-ID is set to 1 and no additional 
                Tx time offset is set. 
                
                Holdover: The data stream does not currently contain a Tx address. 
                The TII last found is sent. 
                
                Ok: TII for the set Tx address is present in the data stream."
            ::= { dabActiveLocalizationEntry 3 }

        
        dabActLclTiiSource OBJECT-TYPE
            SYNTAX DabTiiSource
            MAX-ACCESS read-only
            STATUS current
            DESCRIPTION
                "Indicates which source has been selected for the identifiers 
                of the TII (transmission identification information) settings.
                "
            ::= { dabActiveLocalizationEntry 4 }

        
        dabActiveModulationTable OBJECT-TYPE
            SYNTAX SEQUENCE OF DabActiveModulationEntry
            MAX-ACCESS not-accessible
            STATUS current
            DESCRIPTION
                "Current DAB modulation parameters."
            ::= { dabStatus 4 }

        
        dabActiveModulationEntry OBJECT-TYPE
            SYNTAX DabActiveModulationEntry
            MAX-ACCESS not-accessible
            STATUS current
            DESCRIPTION
                "An entry in the dabActiveModulationTable."
            INDEX { dabStatusNotificationTxIdx, dabStatusNotificationExcIdx }
            ::= { dabActiveModulationTable 1 }

        
        DabActiveModulationEntry ::=
            SEQUENCE { 
                dabActMdlModeEti
                    DabMode,
                dabActMdlMode
                    DabMode
             }

        dabActMdlModeEti OBJECT-TYPE
            SYNTAX DabMode
            MAX-ACCESS read-only
            STATUS current
            DESCRIPTION
                "Indicates which DAB mode is signaled via the ETI header in the data stream."
            ::= { dabActiveModulationEntry 1 }

        
        dabActMdlMode OBJECT-TYPE
            SYNTAX DabMode
            MAX-ACCESS read-only
            STATUS current
            DESCRIPTION
                "Indicates the currently active DAB mode."
            ::= { dabActiveModulationEntry 2 }

        
        dabActiveTiiTable OBJECT-TYPE
            SYNTAX SEQUENCE OF DabActiveTiiEntry
            MAX-ACCESS not-accessible
            STATUS current
            DESCRIPTION
                "Current DAB TII (transmitter identification information) parameters."
            ::= { dabStatus 5 }

        
        dabActiveTiiEntry OBJECT-TYPE
            SYNTAX DabActiveTiiEntry
            MAX-ACCESS not-accessible
            STATUS current
            DESCRIPTION
                "An entry in the dabActiveTiiTable."
            INDEX { dabStatusNotificationTxIdx, dabStatusNotificationExcIdx }
            ::= { dabActiveTiiTable 1 }

        
        DabActiveTiiEntry ::=
            SEQUENCE { 
                dabActTiiMainIdMnsc
                    Unsigned32,
                dabActTiiSubIdMnsc
                    Unsigned32,
                dabActTiiMainId
                    Unsigned32,
                dabActTiiSubId
                    Unsigned32
             }

        dabActTiiMainIdMnsc OBJECT-TYPE
            SYNTAX Unsigned32
            MAX-ACCESS read-only
            STATUS current
            DESCRIPTION
                "Indicates the main ID signaled via MNSC (multiplex network service channel)."
            ::= { dabActiveTiiEntry 1 }

        
        dabActTiiSubIdMnsc OBJECT-TYPE
            SYNTAX Unsigned32
            MAX-ACCESS read-only
            STATUS current
            DESCRIPTION
                "Indicates the sub-ID signaled via MNSC (multiplex network service channel)."
            ::= { dabActiveTiiEntry 2 }

        
        dabActTiiMainId OBJECT-TYPE
            SYNTAX Unsigned32
            MAX-ACCESS read-only
            STATUS current
            DESCRIPTION
                "Indicates the main ID effective in the exciter."
            ::= { dabActiveTiiEntry 3 }

        
        dabActTiiSubId OBJECT-TYPE
            SYNTAX Unsigned32
            MAX-ACCESS read-only
            STATUS current
            DESCRIPTION
                "Indicates the sub-ID effective in the exciter."
            ::= { dabActiveTiiEntry 4 }

        
        dabStatusSfnTable OBJECT-TYPE
            SYNTAX SEQUENCE OF DabStatusSfnEntry
            MAX-ACCESS not-accessible
            STATUS current
            DESCRIPTION
                "Description."
            ::= { dabStatus 6 }

        
        dabStatusSfnEntry OBJECT-TYPE
            SYNTAX DabStatusSfnEntry
            MAX-ACCESS not-accessible
            STATUS current
            DESCRIPTION
                "Description."
            INDEX { dabStatusNotificationTxIdx, dabStatusNotificationExcIdx }
            ::= { dabStatusSfnTable 1 }

        
        DabStatusSfnEntry ::=
            SEQUENCE { 
                dabStSfnTxOffsetDelaySource
                    INTEGER,
                dabStSfnTxOffsetDelayMnsc
                    Unsigned32,
                dabStSfnNetworkCompensationDelay
                    NetworkCompensationDelay,
                dabStSfnTxCompensationDelay
                    Unsigned32,
                dabStSfnTxOffsetDelay
                    Unsigned32,
                dabStSfnMfnOverallSignalDelay
                    Unsigned32
             }

        dabStSfnTxOffsetDelaySource OBJECT-TYPE
            SYNTAX INTEGER
                {
                off(1),
                mnsc(2)
                }
            MAX-ACCESS read-only
            STATUS current
            DESCRIPTION
                "Description."
            ::= { dabStatusSfnEntry 1 }

        
        dabStSfnTxOffsetDelayMnsc OBJECT-TYPE
            SYNTAX Unsigned32
            UNITS "micro second"
            MAX-ACCESS read-only
            STATUS current
            DESCRIPTION
                "Description."
            ::= { dabStatusSfnEntry 2 }

        
        dabStSfnNetworkCompensationDelay OBJECT-TYPE
            SYNTAX NetworkCompensationDelay
            UNITS "micro second"
            MAX-ACCESS read-only
            STATUS current
            DESCRIPTION
                "Indicates the network compensation delay for the opereation in static 
                single frequency networks. If dabSetupSfnSync has been set to static(4), 
                the different feeding time of several transmitters in a SFN can be 
                compensated by the setting of a static transit time correction. The value 
                for the two logical inputs can be set separately.
                
                "
            ::= { dabStatusSfnEntry 3 }

        
        dabStSfnTxCompensationDelay OBJECT-TYPE
            SYNTAX Unsigned32
            UNITS "micro second"
            MAX-ACCESS read-only
            STATUS current
            DESCRIPTION
                "Indicates the time span by which the signal processing 
                is delayed artificially to get a constant Tx Delay."
            ::= { dabStatusSfnEntry 4 }

        
        dabStSfnTxOffsetDelay OBJECT-TYPE
            SYNTAX Unsigned32
            UNITS "micro second"
            MAX-ACCESS read-only
            STATUS current
            DESCRIPTION
                "Indicates the TX Offset Delay. The TX Offset Delay is transmitted via the 
                ETI signalling Channel MNSC (Multiplex Network Service Channel) and 
                is used to set off the time of transmission in comparison with the regular 
                time of transmission pre-determined by the Tx Delay.
                "
            ::= { dabStatusSfnEntry 5 }

        
        dabStSfnMfnOverallSignalDelay OBJECT-TYPE
            SYNTAX Unsigned32 (0..2000000)
            UNITS "micro second"
            MAX-ACCESS read-only
            STATUS current
            DESCRIPTION
                "Indicates the processing delay of the signal through the transmitter."
            ::= { dabStatusSfnEntry 6 }

        
        dabStatusSfnInputTable OBJECT-TYPE
            SYNTAX SEQUENCE OF DabStatusSfnInputEntry
            MAX-ACCESS not-accessible
            STATUS current
            DESCRIPTION
                "current DAB SFN state (by input)."
            ::= { dabStatus 7 }

        
        dabStatusSfnInputEntry OBJECT-TYPE
            SYNTAX DabStatusSfnInputEntry
            MAX-ACCESS not-accessible
            STATUS current
            DESCRIPTION
                "An entry in the dabStatusSfnInputTable"
            INDEX { dabStatusNotificationTxIdx, dabStatusNotificationExcIdx, dabStSfnInputIdx }
            ::= { dabStatusSfnInputTable 1 }

        
        DabStatusSfnInputEntry ::=
            SEQUENCE { 
                dabStSfnInputIdx
                    INTEGER,
                dabStSfnTistState
                    INTEGER,
                dabStSfnNetworkCompensationDelayState
                    NetworkCompensationDelay
             }

        dabStSfnInputIdx OBJECT-TYPE
            SYNTAX INTEGER
                {
                input1(1),
                input2(2)
                }
            MAX-ACCESS not-accessible
            STATUS current
            DESCRIPTION
                "Input index."
            ::= { dabStatusSfnInputEntry 1 }

        
        dabStSfnTistState OBJECT-TYPE
            SYNTAX INTEGER
                {
                undefined(1),
                off(2),
                missingNi(3),
                missingNa(4),
                null(5),
                ok(6),
                flywheelActive(7)
                }
            MAX-ACCESS read-only
            STATUS current
            DESCRIPTION
                "shows, if the input fulfills the requirements of the TIST. "
            ::= { dabStatusSfnInputEntry 2 }

        
        dabStSfnNetworkCompensationDelayState OBJECT-TYPE
            SYNTAX NetworkCompensationDelay
            UNITS "micro second"
            MAX-ACCESS read-only
            STATUS current
            DESCRIPTION
                "Description.
                
                valid, if dabSetupSfnSync is dynamic(3)
                
                "
            ::= { dabStatusSfnInputEntry 3 }

        
        dabSetup OBJECT IDENTIFIER ::= { rsXx9DabObjects 3 }

        
        dabConfigurationTable OBJECT-TYPE
            SYNTAX SEQUENCE OF DabConfigurationEntry
            MAX-ACCESS not-accessible
            STATUS current
            DESCRIPTION
                "General DAB configuration."
            ::= { dabSetup 1 }

        
        dabConfigurationEntry OBJECT-TYPE
            SYNTAX DabConfigurationEntry
            MAX-ACCESS not-accessible
            STATUS current
            DESCRIPTION
                "An entry in the dabConfigurationTable."
            INDEX { dabConfigurationTxIdx, dabConfigurationExcIdx }
            ::= { dabConfigurationTable 1 }

        
        DabConfigurationEntry ::=
            SEQUENCE { 
                dabConfigurationTxIdx
                    IndexTransmitter,
                dabConfigurationExcIdx
                    IndexAB,
                dabConfigurationModeSource
                    DabModeSource
             }

        dabConfigurationTxIdx OBJECT-TYPE
            SYNTAX IndexTransmitter
            MAX-ACCESS not-accessible
            STATUS current
            DESCRIPTION
                "The transmitter index."
            ::= { dabConfigurationEntry 1 }

        
        dabConfigurationExcIdx OBJECT-TYPE
            SYNTAX IndexAB
            MAX-ACCESS not-accessible
            STATUS current
            DESCRIPTION
                "This index distinguishes the exiters.
                Necessary if you have dual drive transmitters."
            ::= { dabConfigurationEntry 2 }

        
        dabConfigurationModeSource OBJECT-TYPE
            SYNTAX DabModeSource
            MAX-ACCESS read-write
            STATUS current
            DESCRIPTION
                "Indicates the DAB mode source. The setting can be changed here. 
                
                Manual: DAB mode is set manually at the transmitter. 
                
                ETI (LI)-MID: DAB mode is read out from the ETI header.
                "
            ::= { dabConfigurationEntry 3 }

        
        dabLocalizationTable OBJECT-TYPE
            SYNTAX SEQUENCE OF DabLocalizationEntry
            MAX-ACCESS not-accessible
            STATUS current
            DESCRIPTION
                "DAB localization parameters."
            ::= { dabSetup 2 }

        
        dabLocalizationEntry OBJECT-TYPE
            SYNTAX DabLocalizationEntry
            MAX-ACCESS not-accessible
            STATUS current
            DESCRIPTION
                "An entry in the dabLocalizationTable."
            AUGMENTS { dabConfigurationEntry }
            ::= { dabLocalizationTable 1 }

        
        DabLocalizationEntry ::=
            SEQUENCE { 
                dabLocalizationTxAddress
                    Unsigned32,
                dabLocalizationTiiSource
                    DabTiiSource
             }

        dabLocalizationTxAddress OBJECT-TYPE
            SYNTAX Unsigned32 (0..65535)
            MAX-ACCESS read-write
            STATUS current
            DESCRIPTION
                "TX address of transmitter."
            ::= { dabLocalizationEntry 1 }

        
        dabLocalizationTiiSource OBJECT-TYPE
            SYNTAX DabTiiSource
            MAX-ACCESS read-write
            STATUS current
            DESCRIPTION
                "see textual convention."
            ::= { dabLocalizationEntry 2 }

        
        dabModulationTable OBJECT-TYPE
            SYNTAX SEQUENCE OF DabModulationEntry
            MAX-ACCESS not-accessible
            STATUS current
            DESCRIPTION
                "DAB modulation parameters."
            ::= { dabSetup 3 }

        
        dabModulationEntry OBJECT-TYPE
            SYNTAX DabModulationEntry
            MAX-ACCESS not-accessible
            STATUS current
            DESCRIPTION
                "An entry in the dabModulationTable."
            AUGMENTS { dabConfigurationEntry }
            ::= { dabModulationTable 1 }

        
        DabModulationEntry ::=
            SEQUENCE { 
                dabModulationChannelBandwidth
                    INTEGER,
                dabModulationMode
                    DabMode
             }

        dabModulationChannelBandwidth OBJECT-TYPE
            SYNTAX INTEGER { mhz1p5(2) }
            MAX-ACCESS read-write
            STATUS current
            DESCRIPTION
                "Channel bandwidth of DAB signal.
                mhz1p5(2) - 1.5 MHz
                "
            ::= { dabModulationEntry 1 }

        
-- The DAB mode if dabConfigurationModeSource is manual(2).
        dabModulationMode OBJECT-TYPE
            SYNTAX DabMode
            MAX-ACCESS read-write
            STATUS current
            DESCRIPTION
                "Indicates which DAB mode has been manually preselected 
                if dabConfigurationModeSource is manual(2).
                "
            ::= { dabModulationEntry 2 }

        
        dabTiiTable OBJECT-TYPE
            SYNTAX SEQUENCE OF DabTiiEntry
            MAX-ACCESS not-accessible
            STATUS current
            DESCRIPTION
                "DAB TII (transmitter identification information) parameters."
            ::= { dabSetup 4 }

        
        dabTiiEntry OBJECT-TYPE
            SYNTAX DabTiiEntry
            MAX-ACCESS not-accessible
            STATUS current
            DESCRIPTION
                "An entry in the dabTiiTable."
            AUGMENTS { dabConfigurationEntry }
            ::= { dabTiiTable 1 }

        
        DabTiiEntry ::=
            SEQUENCE { 
                dabTiiMainId
                    Unsigned32,
                dabTiiSubId
                    Unsigned32,
                dabTiiCarrierPhase
                    INTEGER
             }

        dabTiiMainId OBJECT-TYPE
            SYNTAX Unsigned32 (0..69)
            MAX-ACCESS read-write
            STATUS current
            DESCRIPTION
                "Defines main ID if dabLocalizationTiiSource is manual(2)."
            ::= { dabTiiEntry 1 }

        
        dabTiiSubId OBJECT-TYPE
            SYNTAX Unsigned32 (1..23)
            MAX-ACCESS read-write
            STATUS current
            DESCRIPTION
                "Indicates the set sub-ID. The sub-ID can be used to distinguish 
                between the transmitters within a DAB cell. The setting can be 
                changed here if dabLocalizationTiiSource has been set to manual(2).
                "
            ::= { dabTiiEntry 2 }

        
        dabTiiCarrierPhase OBJECT-TYPE
            SYNTAX INTEGER
                {
                etsi(1),
                prSymbol(2)
                }
            MAX-ACCESS read-write
            STATUS current
            DESCRIPTION
                "Determines the TII Carrier Phase (CP). 
                
                ETSI EN 300 401: The phase of TII carrier pairs are identical 
                according to ETSI EN 300 401. 
                
                PR-Symbol: The phase of TII carrier pairs are not identical 
                according to ETSI EN 300 401.
                "
            ::= { dabTiiEntry 3 }

        
        dabSetupSfnTable OBJECT-TYPE
            SYNTAX SEQUENCE OF DabSetupSfnEntry
            MAX-ACCESS not-accessible
            STATUS current
            DESCRIPTION
                "Description."
            ::= { dabSetup 5 }

        
        dabSetupSfnEntry OBJECT-TYPE
            SYNTAX DabSetupSfnEntry
            MAX-ACCESS not-accessible
            STATUS current
            DESCRIPTION
                "Description."
            AUGMENTS { dabConfigurationEntry }
            ::= { dabSetupSfnTable 1 }

        
        DabSetupSfnEntry ::=
            SEQUENCE { 
                dabSetupSfnSync
                    INTEGER,
                dabSetupSfnTistSource
                    INTEGER,
                dabSetupSfnMaxTistLevel
                    INTEGER,
                dabSetupSfnNetworkCompensationDelay1
                    NetworkCompensationDelay,
                dabSetupSfnNetworkCompensationDelay2
                    NetworkCompensationDelay,
                dabSetupSfnTxDelay
                    Unsigned32,
                dabSetupSfnTxOffsetDelaySource
                    INTEGER
             }

        dabSetupSfnSync OBJECT-TYPE
            SYNTAX INTEGER
                {
                off(2),
                dynamic(3),
                static(4)
                }
            MAX-ACCESS read-write
            STATUS current
            DESCRIPTION
                "Indicates whether the network mode MFN or SFN (dynymic or static) 
                is selected. The setting can be changed here. 
                
                Off (MFN): The time of transmission is not controlled. 
                
                Dynamic (SFN): The time of transmission of a symbol is the same 
                for all the transmitters of a single-frequency network (SFN). The 
                calculation of the  network compensation delays occurs 
                automatically. A GPS receiver is required for synchronization. 
                
                Static (SFN): The time of transmission of a symbol is the same for 
                all the transmitters of a single-frequency network (SFN). The 
                network compensation delay must be determined manually and 
                permanently set.  A constant transit time must be ensured for a 
                accurate function.
                "
            ::= { dabSetupSfnEntry 1 }

        
        dabSetupSfnTistSource OBJECT-TYPE
            SYNTAX INTEGER
                {
                etiLi(3),
                etiNa(4)
                }
            MAX-ACCESS read-write
            STATUS current
            DESCRIPTION
                "Indicates which source is selected for the TIST (timestamp). 
                The setting can be changed here, if dabSetupSfnSync has 
                been set to dynamic(3). It can be used the TIST either from 
                the ETI (LI) frame or the ETI (NA) frame.
                "
            ::= { dabSetupSfnEntry 2 }

        
        dabSetupSfnMaxTistLevel OBJECT-TYPE
            SYNTAX INTEGER
                {
                off(2),
                level1(3),
                level2(4),
                level3(5),
                level4(6),
                level5(7)
                }
            MAX-ACCESS read-write
            STATUS current
            DESCRIPTION
                "Indicates the accuracy of the analysis of the timestamp. 
                On principle the highest possible level must be used 
                which is supported by the ensemble multiplexer and all 
                other transmiiters in the network. Level 4 correponds to 
                488 ns. The setting of the level can be changed here, if 
                dabSetupSfnSync has been set to dynamic(3).
                "
            ::= { dabSetupSfnEntry 3 }

        
        dabSetupSfnNetworkCompensationDelay1 OBJECT-TYPE
            SYNTAX NetworkCompensationDelay
            UNITS "micro second"
            MAX-ACCESS read-write
            STATUS current
            DESCRIPTION
                "Network compensation delay for logical input 1.
                
                Indicates the network compensation delay for the opereation in static 
                single frequency networks. If dabSetupSfnSync has been set to static(4), 
                the different feeding time of several transmitters in a SFN can be 
                compensated by the setting of a static  transit time correction. The value 
                for the two logical inputs can be set separately.
                "
            ::= { dabSetupSfnEntry 4 }

        
        dabSetupSfnNetworkCompensationDelay2 OBJECT-TYPE
            SYNTAX NetworkCompensationDelay
            UNITS "micro second"
            MAX-ACCESS read-write
            STATUS current
            DESCRIPTION
                "Network compensation delay for logical input 2.
                
                Indicates the network compensation delay for the opereation in static 
                single frequency networks. If dabSetupSfnSync has been set to static(4), 
                the different feeding time of several transmitters in a SFN can be 
                compensated by the setting of a static  transit time correction. The value 
                for the two logical inputs can be set separately.
                "
            ::= { dabSetupSfnEntry 5 }

        
        dabSetupSfnTxDelay OBJECT-TYPE
            SYNTAX Unsigned32 (0..1000000)
            UNITS "micro second"
            MAX-ACCESS read-write
            STATUS current
            DESCRIPTION
                "Indicates the transit time of the signal through the 
                transmitter. The transit time is the sum of Tx 
                Compensation Delay and Tx Processing Delay."
            ::= { dabSetupSfnEntry 6 }

        
        dabSetupSfnTxOffsetDelaySource OBJECT-TYPE
            SYNTAX INTEGER
                {
                off(1),
                mnsc(2)
                }
            MAX-ACCESS read-write
            STATUS current
            DESCRIPTION
                "Choose whether a transmitter specific offset delay is 
                taken from the Multiplex Network Service Channel.
                "
            ::= { dabSetupSfnEntry 7 }

        
        dabTestTable OBJECT-TYPE
            SYNTAX SEQUENCE OF DabTestEntry
            MAX-ACCESS not-accessible
            STATUS current
            DESCRIPTION
                "Configures the test mode of the exciter."
            ::= { dabSetup 6 }

        
        dabTestEntry OBJECT-TYPE
            SYNTAX DabTestEntry
            MAX-ACCESS not-accessible
            STATUS current
            DESCRIPTION
                "An entry in the dabTestTable."
            AUGMENTS { dabConfigurationEntry }
            ::= { dabTestTable 1 }

        
        DabTestEntry ::=
            SEQUENCE { 
                dabTestSignal
                    INTEGER,
                dabTestRsEnsembleDataChannel
                    INTEGER,
                dabTestRsEnsemblePrbs
                    INTEGER
             }

        dabTestSignal OBJECT-TYPE
            SYNTAX INTEGER
                {
                off(1),
                rohdeSchwarzEnsemble(2),
                singleCarrier(3)
                }
            MAX-ACCESS read-write
            STATUS current
            DESCRIPTION
                "Indicates which test signal is to be generated.
                
                off(1):         - switches off test signal generation.
                rohdeSchwarzEnsemble(2):  - Generates an ETI(LI) signal insted of the 
                                  payload.
                singleCarrier(3): - Generates an unmodulated single carrier. 
                
                This test signal can be used to measure the phase noise of the 
                synthesizer. The phase noise must be measured via the RF Monitor Out 
                connector (X61). The cable connected to RF Out (X60) must be removed. 
                In order to protect the amplifiers, this test signal is only generated if the 
                output of the exciter is open.
                "
            ::= { dabTestEntry 1 }

        
        dabTestRsEnsembleDataChannel OBJECT-TYPE
            SYNTAX INTEGER
                {
                off(1),
                prbs(2)
                }
            MAX-ACCESS read-write
            STATUS current
            DESCRIPTION
                "Indicates which PRBS Sequence shall be inserted to the data channel:
                To activate PRBS insertion the parameter dabTestSignal has to 
                be set to rohdeSchwarzEnsemble(2). 
                off(1): A PRBS sequence is inserted to the audio channel only. 
                prbs(2): A PRBS sequence is inserted to the audio and data channel. 
                The setting can be changed here.
                "
            ::= { dabTestEntry 2 }

        
        dabTestRsEnsemblePrbs OBJECT-TYPE
            SYNTAX INTEGER
                {
                poly1(1),
                poly2(2),
                poly3(3)
                }
            MAX-ACCESS read-write
            STATUS current
            DESCRIPTION
                "Indicates which pseudo random binary sequence shall be inserted to 
                the audio and/or data channels. To activate PRBS insertion the 
                parameter dabTestSignal has to be set to rohdeSchwarzEnsemble(2). 
                The setting can be changed here.
                
                poly1(1) - x^20+x^17+1
                poly2(2) - x^23+x^18+1
                poly3(3) - x^15+x^14+1
                "
            ::= { dabTestEntry 3 }

        
        rsXx9DabConformance OBJECT IDENTIFIER ::= { rsXx9Dab 2 }

        
        rsXx9DabCompliances OBJECT IDENTIFIER ::= { rsXx9DabConformance 1 }

        
        dabBasicCompliance MODULE-COMPLIANCE
            STATUS current
            DESCRIPTION 
                "The compliance statement for XX9000 DAB encoding."
            MODULE -- this module
                MANDATORY-GROUPS { dabObjBasic, dabNotifyBasic, dabObjInput }
            ::= { rsXx9DabCompliances 1 }

        
        rsXx9DabGroups OBJECT IDENTIFIER ::= { rsXx9DabConformance 2 }

        
        dabObjBasic OBJECT-GROUP
            OBJECTS { dabConfigurationModeSource, dabLocalizationTxAddress, dabLocalizationTiiSource, dabTestSignal, dabTiiSubId, 
                dabTiiMainId, dabModulationChannelBandwidth, dabActCfgModeSource, dabActLclTxAddressPresentPlain, dabActLclTxAddressRequired, 
                dabActLclTiiSource, dabActMdlMode, dabActTiiMainIdMnsc, dabActTiiSubIdMnsc, dabActTiiMainId, 
                dabActTiiSubId, dabActMdlModeEti, dabActLclTxAddressState, dabSetupSfnSync, dabSetupSfnTistSource, 
                dabSetupSfnMaxTistLevel, dabSetupSfnNetworkCompensationDelay1, dabSetupSfnNetworkCompensationDelay2, dabSetupSfnTxDelay, dabStSfnTxOffsetDelaySource, 
                dabStSfnTxOffsetDelayMnsc, dabStSfnNetworkCompensationDelay, dabStSfnTxCompensationDelay, dabStSfnTxOffsetDelay, dabStSfnTistState, 
                dabTiiCarrierPhase, dabSetupSfnTxOffsetDelaySource, dabStSfnNetworkCompensationDelayState, dabStSfnMfnOverallSignalDelay, dabTestRsEnsemblePrbs, 
                dabTestRsEnsembleDataChannel, dabModulationMode, dabStatusNotificationName, dabStatusNotificationMask, dabStatusNotificationPriority, 
                dabStatusNotificationState }
            STATUS current
            DESCRIPTION 
                "General DAB objects."
            ::= { rsXx9DabGroups 1 }

        
        dabObjInput OBJECT-GROUP
            OBJECTS { dabInputEtiDatarateState, dabInputEtiDatarate, dabInputEtiErrorLevelState, dabInputNotificationState, dabInputNotificationPriority, 
                dabInputNotificationMask, dabInputNotificationName, dabInputEdiFecMode, dabInputEdiReplacementStatus, dabInputEdiErrorLevelState, 
                dabInputEdiDatarateState, dabInputEdiStreamPort, dabInputEdiStreamAddress, dabInputEdiStreamAddressType, dabInputEdiStreamingMode, 
                dabInputEdiConnector, dabInputEdiDatarate, dabInputCmnEdiMaxReplacements, dabInputCmnEdiDejitterBuffer, dabInputEtiSyncState, 
                dabInputCmnImpedance, dabInputEdiSyncState }
            STATUS current
            DESCRIPTION 
                "DAB input objects."
            ::= { rsXx9DabGroups 2 }

        
        dabNotifyBasic NOTIFICATION-GROUP
            NOTIFICATIONS { dabTiiMainIdOutOfRange, dabEncoderSummary, dabTest, dabInpIfEtiState, dabInpIfEdiState
                 }
            STATUS current
            DESCRIPTION 
                "General DAB notifications."
            ::= { rsXx9DabGroups 3 }

        
    
    END

--
-- RS-XX9-DAB-MIB.mi2
--
