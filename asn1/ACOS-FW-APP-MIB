ACOS-FW-APP-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		fwAppModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "fwAppModule OID for ACOS"
				::=  {  acosSchema 477 }

app		 OBJECT IDENTIFIER ::= { fwAppModule 1}

appStatsTable OBJECT-TYPE
	 SYNTAX SEQUENCE OF AppStatsEntry
	 MAX-ACCESS not-accessible
	 STATUS current
	 DESCRIPTION
	 "Show application firewall supported protocols from object 'fw.app'"
	::= {app 1}

appStatsEntry OBJECT-TYPE
	SYNTAX AppStatsEntry
	MAX-ACCESS not-accessible
	STATUS current
	DESCRIPTION
		"The appStats stats entry"
	INDEX {
		appStatsSlotId
	}
	::= { appStatsTable 1 }

AppStatsEntry ::=
	SEQUENCE {
		appStatsSlotId Integer32,
		appStatsDummy	 CounterBasedGauge64
	}

appStatsSlotId OBJECT-TYPE
	 SYNTAX Integer32
	 MAX-ACCESS read-only
	 STATUS current
	 DESCRIPTION
		 ""
	::= { appStatsEntry 1 }

appStatsDummy OBJECT-TYPE
	 SYNTAX Integer32
	 MAX-ACCESS read-only
	 STATUS current
	 DESCRIPTION
		 "dummy"
	::= { appStatsEntry 2 }

appOperTable OBJECT-TYPE
	 SYNTAX SEQUENCE OF AppOperEntry
	 MAX-ACCESS not-accessible
	 STATUS current
	 DESCRIPTION
		 "Show application firewall supported protocols from object 'fw.app'"
	::= {app 2}

appOperEntry OBJECT-TYPE
	SYNTAX AppOperEntry
	MAX-ACCESS not-accessible
	STATUS current
	DESCRIPTION
		"The appOper entry"
	INDEX {
		appOperSlotId
	}
	::= { appOperTable 1 }

AppOperEntry ::=
	SEQUENCE {
		appOperSlotId Integer32,
		appOperCategory	 DisplayString,
		appOperContains	 DisplayString,
		appOperRelated	 DisplayString
	}

appOperSlotId OBJECT-TYPE
	 SYNTAX Integer32
	 MAX-ACCESS read-only
	 STATUS current
	 DESCRIPTION
		 ""
	::= { appOperEntry 1 }

appOperCategory OBJECT-TYPE
	 SYNTAX DisplayString
	 MAX-ACCESS read-only
	 STATUS current
	 DESCRIPTION
		 "category"
	::= { appOperEntry 2 }

appOperContains OBJECT-TYPE
	 SYNTAX DisplayString
	 MAX-ACCESS read-only
	 STATUS current
	 DESCRIPTION
		 "contains"
	::= { appOperEntry 3 }

appOperRelated OBJECT-TYPE
	 SYNTAX DisplayString
	 MAX-ACCESS read-only
	 STATUS current
	 DESCRIPTION
		 "related"
	::= { appOperEntry 4 }

appOperGroupListTable OBJECT-TYPE
	 SYNTAX SEQUENCE OF AppOperGroupListEntry
	 MAX-ACCESS not-accessible
	 STATUS current
	 DESCRIPTION
		 "Show application firewall supported protocols from object 'fw.app'"
	::= {app 3}

appOperGroupListEntry OBJECT-TYPE
	SYNTAX AppOperGroupListEntry
	MAX-ACCESS not-accessible
	STATUS current
	DESCRIPTION
		"The appOperGroupList entry:group-list"
	INDEX {
		appOperGroupListSlotId,
		appOperGroupListGroupListListId
	}
	::= { appOperGroupListTable 1}

AppOperGroupListEntry ::=
	SEQUENCE {
		appOperGroupListSlotId Integer32,
		appOperGroupListGroupListListId Integer32,
		appOperGroupListCategoryName	DisplayString,
		appOperGroupListAppName	DisplayString,
		appOperGroupListAppDesc	DisplayString
	}

appOperGroupListSlotId OBJECT-TYPE
	SYNTAX Integer32
	MAX-ACCESS read-only
	STATUS current
	DESCRIPTION
		""
	::= { appOperGroupListEntry 1}

appOperGroupListGroupListListId OBJECT-TYPE
	SYNTAX Integer32
	MAX-ACCESS read-only
	STATUS current
	DESCRIPTION
		""
	::= { appOperGroupListEntry 2}

appOperGroupListCategoryName OBJECT-TYPE
	SYNTAX DisplayString
	MAX-ACCESS read-only
	STATUS current
	DESCRIPTION
		"category-name"
	::= { appOperGroupListEntry 3}

appOperGroupListAppName OBJECT-TYPE
	SYNTAX DisplayString
	MAX-ACCESS read-only
	STATUS current
	DESCRIPTION
		"app-name"
	::= { appOperGroupListEntry 4}

appOperGroupListAppDesc OBJECT-TYPE
	SYNTAX DisplayString
	MAX-ACCESS read-only
	STATUS current
	DESCRIPTION
		"app-desc"
	::= { appOperGroupListEntry 5}

END
