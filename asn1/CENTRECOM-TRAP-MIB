--/* 
-- * $RCSfile: atkkext.mib $ - ATKK Model CentreCOM 8500 and 9100 Enterprise MIB
-- *
-- * Copyright (c) 1997-8 by Extreme Networks Inc.
-- * 
-- *	  Allied Telesis K.K
-- *      http://www1.allied-telesis.co.jp/GIGA
-- *
-- *
-- * Revision control history
-- * ------------------------
-- * $Id: atkkext.mib 1.4 1998/11/12 22:30:11 abhatt PR3811 abhatt $ $Name: PR3811 $ $ProjectRevision: 1.118.1.9 $
-- *
-- * modification history
-- * --------------------
-- * $Log: atkkext.mib $
-- * Revision 1.4  1998/11/12 22:30:11  abhatt
-- * Revision 1.3  1998/11/12 22:28:49  abhatt
-- * Modified the enterprise-name, www-site-address, etc. globally.
-- * Revision 1.2  1998/11/09 22:48:16  abhatt
-- * Changed file name from atkk.mib to atkkext.mib upon request.
-- * Revision 1.1  1998/11/09 22:41:34  abhatt
-- * Initial revision
-- * Revision 1.4  1998/10/20 00:56:06  abhatt
-- * Revision 1.3  1998/10/20 00:52:51  abhatt
-- * PR3715
-- * Revision 1.2  1998/04/15 20:41:04  asmith
-- * add <CR> to make HPOV happy
-- * Revision 1.1  1998/02/19 23:02:51  asmith
-- * Initial revision
-- */

-- ===============================================================================

--
-- Traps
--

CENTRECOM-TRAP-MIB DEFINITIONS ::= BEGIN

        IMPORTS
                extSwitchMIB                   FROM CENTRECOM-MIB
		sysUpTime, sysDescr             FROM RFC1213-MIB
                TRAP-TYPE                       FROM RFC-1215;

          overheat TRAP-TYPE
              ENTERPRISE  extSwitchMIB
              VARIABLES   { sysUpTime, sysDescr }
              DESCRIPTION
                          "A overheat trap indicates that the on board
                          tempature sensor has reported a overheat 
                          condition.  System will shutdown until unit has
			  sufficiently cooled such that operation may begin
                          again.  A cold start trap will be issued when
                          the unit has come back on line."    
              ::= 6

          fanfailed TRAP-TYPE
              ENTERPRISE  extSwitchMIB
              VARIABLES   { sysUpTime, sysDescr }
              DESCRIPTION
                          "A fan failed trap indicates one or more of the
                          cooling fans inside the device has failed.  A
                          fanOK trap will be sent once the fan has attained
                          normal operation."
              ::= 7

          fanOK TRAP-TYPE
              ENTERPRISE  extSwitchMIB
              VARIABLES   { sysUpTime, sysDescr }
              DESCRIPTION
                          "A fan has transitioned out of a failure state and
                          is now operating correctly."
              ::= 8

          invalidLoginAttempt TRAP-TYPE
              ENTERPRISE  extSwitchMIB
              VARIABLES   { sysUpTime, sysDescr }
              DESCRIPTION
                          "A user attempted to login to console or by telnet but was refused
                           access due to incorrect username or password"
              ::= 9

          powerSupplyFail TRAP-TYPE
              ENTERPRISE  extSwitchMIB
              VARIABLES   { sysUpTime, sysDescr }
              DESCRIPTION
                          "One or more sources of power to this agent has failed.
                           Presumably a redundant power-supply has taken over."
              ::= 10

          powerSupplyGood TRAP-TYPE
              ENTERPRISE  extSwitchMIB
              VARIABLES   { sysUpTime, sysDescr }
              DESCRIPTION
                          "One or more previously bad sources of power to this agent 
                           has come back to life without causing an agent restart."
              ::= 11

          rpsAlarm TRAP-TYPE
              ENTERPRISE  extSwitchMIB
              VARIABLES   { sysUpTime, sysDescr }
              DESCRIPTION
                          "Attached Redundant Power Supply device is indicating
                           an alarm condition."
              ::= 12

          rpsNoAlarm TRAP-TYPE
              ENTERPRISE  extSwitchMIB
              VARIABLES   { sysUpTime, sysDescr }
              DESCRIPTION
                          "Attached Redundant Power Supply device is no longer
                           indicating an alarm condition."
              ::= 13


END
