--
-- PBN-MIB.mib
-- MIB generated by MG-SOFT Visual MIB Builder Version 7.0  Build 220
-- Friday, May 09, 2008 at 13:45:10
--

-- **************************************************************************
-- File PBN.mib
-- 
-- 
-- Copyright (C)2007 by PBN Networks
-- 
-- 
-- MODULE-IDENTITY
-- 
-- Last Updated : 06 JULY 2007
-- 
-- OrgName
-- Pacific Broadband Networks
-- 
-- ContactInfo
-- 8-10 Keith Campbell Court, 
-- SCORESBY VIC 3179,
-- Australia
-- Telephone: +61-3-9763-1800
-- Facsimile: +61-3-9763-5522
-- e-mail nms3@pbn.com.au
-- 
-- Description
-- MIB for the PBN advance optic products
-- 
-- Version - dependencies
-- 
-- 
-- History :
--  13-Mar-08 - Added MAU module and associated traps
--                   - Additional generic types for common reference
--  06/07/2007 - Added FPCM
--  04/01/2006 - Update for OSLAM-8G for beta product release
--  12/12/2006 - Updated comments for CPON-100
--             - Updating OSLAM-8G table
--  10/11/2006 - Adding OSLAM-8G
--  31/08/2006 - Adding CPON-100
--  20/03/2006 - Update "ContactInfo"
--  30/11/2002 - Second draft
--  02/08/2002 - First draft
-- **************************************************************************

	PBN-MIB DEFINITIONS ::= BEGIN
 
		IMPORTS
			OBJECT-TYPE			
				FROM RFC-1212			
			TRAP-TYPE			
				FROM RFC-1215			
			enterprises, IpAddress, Counter, Opaque			
				FROM RFC1155-SMI			
			DisplayString			
				FROM RFC1213-MIB;
	
	
--
-- Type definitions
--
	
		TypePowerSupply ::= INTEGER
			{
			ac220V(1),
			ac60V(2)
			}

		TypeTamper ::= INTEGER
			{
			open(1),
			yes(2)
			}

		TypeYesNo ::= INTEGER
			{
			no(1),
			yes(2)
			}

		TypeOnOff ::= INTEGER
			{
			off(1),
			on(2)
			}

		TypeAGCStatus ::= INTEGER
			{
			unlock(1),
			lock(2)
			}

		TypeGainMode ::= INTEGER
			{
			auto(1),
			manual(2)
			}

	
--
-- Node definitions
--
	
		-- 1.3.6.1.4.1.11606
		pbn OBJECT IDENTIFIER ::= { enterprises 11606 }

		
-- PBN Enterprise trap
		-- 1.3.6.1.4.1.11606.0
		pbnTrap OBJECT IDENTIFIER ::= { pbn 0 }

		
-- OCM: Optical Communication Mainframe chassis
-- ============================================
-- Supported all Series 2 and Series 3 OCM
		-- 1.3.6.1.4.1.11606.1
		ocm OBJECT IDENTIFIER ::= { pbn 1 }

		
-- **************************************************************************
-- ***************** OCM - OCMF, OCMR, OCMC ******************************
-- **************************************************************************
-- **************************************************************************
-- PBNDevice : The devices managed by PBN Network Management System
		-- 1.3.6.1.4.1.11606.1.1
		pbnDevice OBJECT-TYPE
			SYNTAX INTEGER (1 | 2 | 30)
			ACCESS read-only
			STATUS mandatory
			DESCRIPTION
				"PBN Networks Management Devices"
			::= { ocm 1 }

		
-- **************************************************************************
-- PBNDeviceAddress : The devices managed by PBN Network Management System
		-- 1.3.6.1.4.1.11606.1.2
		deviceAddress OBJECT-TYPE
			SYNTAX INTEGER (0..255)
			ACCESS read-write
			STATUS mandatory
			DESCRIPTION
				"PBN Networks Management Device Address"
			::= { ocm 2 }

		
-- **************************************************************************
-- OCMSlot : The OCM slot of the PBN device
		-- 1.3.6.1.4.1.11606.1.3
		ocmSlot OBJECT-TYPE
			SYNTAX INTEGER (0..8)
			ACCESS read-write
			STATUS mandatory
			DESCRIPTION
				"The OCM slot of the PBN device"
			::= { ocm 3 }

		
-- **************************************************************************
-- OCMPage : The device page
		-- 1.3.6.1.4.1.11606.1.4
		ocmPage OBJECT-TYPE
			SYNTAX INTEGER (0..7)
			ACCESS read-write
			STATUS mandatory
			DESCRIPTION
				"The Device Page"
			::= { ocm 4 }

		
-- **************************************************************************
-- OCMParam : The OCM Parameter
		-- 1.3.6.1.4.1.11606.1.5
		ocmParam OBJECT-TYPE
			SYNTAX INTEGER (0..31)
			ACCESS read-write
			STATUS mandatory
			DESCRIPTION
				"The Device Parameter"
			::= { ocm 5 }

		
-- **************************************************************************
-- OCMParamStatus : The OCM Param Status
		-- 1.3.6.1.4.1.11606.1.6
		ocmParamStatus OBJECT-TYPE
			SYNTAX INTEGER (0..3)
			ACCESS read-only
			STATUS mandatory
			DESCRIPTION
				"The parameter status"
			::= { ocm 6 }

		
-- **************************************************************************
-- OCMParamString : The OCM Parameter String
		-- 1.3.6.1.4.1.11606.1.7
		ocmParamString OBJECT-TYPE
			SYNTAX DisplayString
			ACCESS read-only
			STATUS mandatory
			DESCRIPTION
				"The parameter string"
			::= { ocm 7 }

		
-- **************************************************************************
-- OCMWriteParameterValue : The OCM Write Parameter Value
		-- 1.3.6.1.4.1.11606.1.8
		ocmWriteParameterValue OBJECT-TYPE
			SYNTAX INTEGER
			ACCESS read-write
			STATUS mandatory
			DESCRIPTION
				"The Write Parameter Value ID"
			::= { ocm 8 }

		
-- **************************************************************************
-- OCMToggleParameterValue : The OCM Toggle Parameter Value
		-- 1.3.6.1.4.1.11606.1.9
		ocmToggleParameterValue OBJECT-TYPE
			SYNTAX INTEGER
			ACCESS read-write
			STATUS mandatory
			DESCRIPTION
				"The Toggle Parameter Value ID"
			::= { ocm 9 }

		
-- **************************************************************************
-- ****************************** CPON-100 **********************************
-- **************************************************************************
-- **************************************************************************
-- OCMReadParameterValue : The OCM Read Parameter Value
		-- 1.3.6.1.4.1.11606.1.10
		ocmReadParameterValue OBJECT-TYPE
			SYNTAX INTEGER
			ACCESS read-only
			STATUS mandatory
			DESCRIPTION
				"The Toggle Parameter Value ID"
			::= { ocm 10 }

		
-- CPON-100: Customer Premises Optical Node for fast Ethernet and CATV.
-- ====================================================================
-- The unit provides future-proof high bandwidth via fibre to the home services (FTTH).
-- The integrated fibre splice organiser negates the need for extra boxes.
-- The compact design has been tailored with security and ease of installation in mind.
		-- 1.3.6.1.4.1.11606.2
		cpon100 OBJECT IDENTIFIER ::= { pbn 2 }

		
-- CPON-100 trap
		-- 1.3.6.1.4.1.11606.2.0
		cpon100Trap OBJECT IDENTIFIER ::= { cpon100 0 }

		
-- CATV power ON/OFF control:
-- (0) - Disable CATV service
-- (1) - Enable CATV service
		-- 1.3.6.1.4.1.11606.2.1
		catvCtrl OBJECT-TYPE
			SYNTAX INTEGER (0..1)
			ACCESS read-write
			STATUS mandatory
			DESCRIPTION
				"CATV Service Control"
			::= { cpon100 1 }

		
-- Master alarm status: Currently not used.
-- (0) - Master alarm OFF
-- (1) - Master alarm ON
		-- 1.3.6.1.4.1.11606.2.2
		masterAlarmStatus OBJECT-TYPE
			SYNTAX INTEGER (0..1)
			ACCESS read-only
			STATUS obsolete
			DESCRIPTION
				"Master Alarm Status"
			::= { cpon100 2 }

		
-- Contact input aka. Tamper status:
-- (0) - Contact CLOSE
-- (1) - Contact OPEN
		-- 1.3.6.1.4.1.11606.2.3
		contactInput OBJECT-TYPE
			SYNTAX INTEGER (0..1)
			ACCESS read-only
			STATUS mandatory
			DESCRIPTION
				"Tamper Status"
			::= { cpon100 3 }

		
-- CATV optical status:
-- (0) - CATV-RX not present
-- (1) - Urgent alarm (optical high)
-- (2) - OK
-- (3) - Non-Urgent alarm (optical low)
		-- 1.3.6.1.4.1.11606.2.4
		catvStatus OBJECT-TYPE
			SYNTAX INTEGER (0..3)
			ACCESS read-only
			STATUS mandatory
			DESCRIPTION
				"CATV Service Status"
			::= { cpon100 4 }

		
-- Sensing input:
-- (0) - OFF or CLOSE
-- (1) - ON or OPEN
		-- 1.3.6.1.4.1.11606.2.5
		sensingInput OBJECT-TYPE
			SYNTAX INTEGER (0..1)
			ACCESS read-only
			STATUS mandatory
			DESCRIPTION
				"Sensing Input"
			::= { cpon100 5 }

		
-- Global packet size support:
-- (0) - Accept max packet size 1522 for tagged packets and 
--       1518 for untagged packets.
-- (1) - Accept packet size of up to 1536
-- (2) - Accept packet size of up to 1916
		-- 1.3.6.1.4.1.11606.2.6
		globalPktSize OBJECT-TYPE
			SYNTAX INTEGER (0..2)
			ACCESS read-write
			STATUS mandatory
			DESCRIPTION
				"Packet Size"
			::= { cpon100 6 }

		
-- Multicast storm protection:
-- (0) - "Broadcast Storm Protection" includes DA=FFFFFFFFFFFF 
--       and DA[40] = 1 packets
-- (1) - "Broadcast Storm Protection" does not include multicast packets.
--       Only DA=FFFFFFFFFFFF packets will be regulated.
		-- 1.3.6.1.4.1.11606.2.7
		globalMulticastStormProtection OBJECT-TYPE
			SYNTAX INTEGER (0..1)
			ACCESS read-write
			STATUS mandatory
			DESCRIPTION
				"Multicast Storm Protection"
			::= { cpon100 7 }

		
-- Flow control enable/disable:
-- (0) - Will enable both TRANSMIT and RECEIVE flow control based on Auto-Negotiation result.
-- 
-- (1) - Will not enable RECEIVE flow control based regardless of strap option
--       and 
--       Will enable TRANSMIT flow control based on Auto-Negotiation result.
-- 
-- (2) - Will not enable TRANSMIT flow control based regardless of strap option
--       and
--       Will enable RECEIVE flow control based on Auto-Negotiation result.
-- 
-- (3) - Disable both TRANSMIT and RECEIVE flow control regardless of strap option.
		-- 1.3.6.1.4.1.11606.2.8
		globalFlowCtrl OBJECT-TYPE
			SYNTAX INTEGER (0..3)
			ACCESS read-write
			STATUS mandatory
			DESCRIPTION
				"Flow Control"
			::= { cpon100 8 }

		
-- Back pressure mode:
-- (0) - Collision based back pressure selected.
-- (1) - Carrier sense based back pressure selected.
		-- 1.3.6.1.4.1.11606.2.9
		globalBackPressureMode OBJECT-TYPE
			SYNTAX INTEGER (0..1)
			ACCESS read-write
			STATUS mandatory
			DESCRIPTION
				"Back Pressure Mode"
			::= { cpon100 9 }

		
-- Priority buffer reserve:
-- (0) - No reserved buffers for high priority packets.
-- (1) - Each output queue is pre-allocated 48 buffers, 
--       used exclusively for hig priority packets. 
--       It is recommended to enable this when priority 
--       queue feature is turned on.
-- 
		-- 1.3.6.1.4.1.11606.2.10
		globalPriorityBufferReserve OBJECT-TYPE
			SYNTAX INTEGER (0..1)
			ACCESS read-write
			STATUS mandatory
			DESCRIPTION
				"Priority Buffer Reserve"
			::= { cpon100 10 }

		
-- Priority scheme select:
-- (0) - Always deliver high priority packets first.
-- (1) - Deliver high/low packets at ration 10/1
-- (2) - Deliver high/low packets at ration 5/1
-- (3) - Deliver high/low packets at ration 2/1
		-- 1.3.6.1.4.1.11606.2.11
		globalPriorityScheme OBJECT-TYPE
			SYNTAX INTEGER (0..3)
			ACCESS read-write
			STATUS mandatory
			DESCRIPTION
				"Priority Scheme Select"
			::= { cpon100 11 }

		
-- 802.1p Based priority:
-- Used to classify priority for incoming 802.1q packets "Use priority" 
-- is compared against this value.
-- (+): classified as priority 
-- <: classified as low priority
		-- 1.3.6.1.4.1.11606.2.12
		global802dot1PBasedPriority OBJECT-TYPE
			SYNTAX INTEGER (0..7)
			ACCESS read-write
			STATUS mandatory
			DESCRIPTION
				"802.1p Based priority"
			::= { cpon100 12 }

		
-- 802.1q VLAN enable:
-- (0) - 802.1q VLAN is disabled.
-- (1) - 802.1q VLAN mode is turned on. VLAN table needs to set 
--       up before the operation.
		-- 1.3.6.1.4.1.11606.2.13
		global802dot1qVLANEnable OBJECT-TYPE
			SYNTAX INTEGER (0..1)
			ACCESS read-write
			STATUS mandatory
			DESCRIPTION
				"802.1q VLAN enable"
			::= { cpon100 13 }

		
-- Null VID Replacement:
-- (0) - No replacement for null VID.
-- (1) - Replace NULL VID with port VID (12bits)
		-- 1.3.6.1.4.1.11606.2.14
		globalNullVIDReplacement OBJECT-TYPE
			SYNTAX INTEGER (0..1)
			ACCESS read-write
			STATUS mandatory
			DESCRIPTION
				"Null VID Replacement"
			::= { cpon100 14 }

		
-- Source address MAC pause control frame:
-- 48bit MAC address
		-- 1.3.6.1.4.1.11606.2.15
		sourceMACPauseCtrl OBJECT-TYPE
			SYNTAX Opaque (SIZE (6))
			ACCESS read-write
			STATUS mandatory
			DESCRIPTION
				"Source Address MAC Pause"
			::= { cpon100 15 }

		
-- Fast age enable:
-- (0) - Turn off fast age
-- (1) - Turn on fast age (800us)
		-- 1.3.6.1.4.1.11606.2.16
		globalFastAge OBJECT-TYPE
			SYNTAX INTEGER (0..1)
			ACCESS read-write
			STATUS mandatory
			DESCRIPTION
				"Fast Age"
			::= { cpon100 16 }

		
-- MAC address.
		-- 1.3.6.1.4.1.11606.2.17
		cpon100MACAddr OBJECT-TYPE
			SYNTAX OCTET STRING (SIZE (0..5))
			ACCESS read-only
			STATUS mandatory
			DESCRIPTION
				"CPON-100 SNMP MAC Address"
			::= { cpon100 17 }

		
-- Trap severity
-- 0 - Normal
-- 1 - Non-Urgent
-- 2 - Urgent
		-- 1.3.6.1.4.1.11606.2.18
		cpon100TrapStatus OBJECT-TYPE
			SYNTAX INTEGER (0..2)
			ACCESS read-only
			STATUS mandatory
			DESCRIPTION
				"CPON-100 Trap severity"
			::= { cpon100 18 }

		
-- Trap Message
		-- 1.3.6.1.4.1.11606.2.19
		cpon100TrapMsg OBJECT-TYPE
			SYNTAX DisplayString (SIZE (0..63))
			ACCESS read-only
			STATUS mandatory
			DESCRIPTION
				"CPON-100 Trap Message"
			::= { cpon100 19 }

		
-- CPON-100 VLAN Table
		-- 1.3.6.1.4.1.11606.2.21
		vlanTable OBJECT IDENTIFIER ::= { cpon100 21 }

		
-- CPON-100 VLAN1
		-- 1.3.6.1.4.1.11606.2.21.1
		vlanAddr1 OBJECT-TYPE
			SYNTAX INTEGER (0..16777215)
			ACCESS read-write
			STATUS mandatory
			DESCRIPTION
				"CPON-100-100 VLAN1"
			::= { vlanTable 1 }

		
-- CPON-100  VLAN2
		-- 1.3.6.1.4.1.11606.2.21.2
		vlanAddr2 OBJECT-TYPE
			SYNTAX INTEGER (0..16777215)
			ACCESS read-write
			STATUS mandatory
			DESCRIPTION
				"CPON-100 VLAN2"
			::= { vlanTable 2 }

		
-- CPON-100 VLAN3
		-- 1.3.6.1.4.1.11606.2.21.3
		vlanAddr3 OBJECT-TYPE
			SYNTAX INTEGER (0..16777215)
			ACCESS read-write
			STATUS mandatory
			DESCRIPTION
				"CPON-100 VLAN3"
			::= { vlanTable 3 }

		
-- CPON-100 Static MAC Table
		-- 1.3.6.1.4.1.11606.2.22
		staticMACTable OBJECT IDENTIFIER ::= { cpon100 22 }

		
-- Static MAC Address entry 1:
-- When reading data from this OID
-- ===============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Reserve
-- BIT[56]   - Use FID
--             (0) - Use MAC only to lookup in static table
--             (1) - Use (FID+MAC) to lookup in static table
-- BIT[57:60]- Filter VLAN ID, representing on of the 16 active VLANs
-- 
-- When writing data to this OID
-- ==============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Use FID
--             (0) - Use MAC only to lookup in static table
--             (1) - Use (FID+MAC) to lookup in static table
-- BIT[56:59]- Filter VLAN ID, representing on of the 16 active VLANs
		-- 1.3.6.1.4.1.11606.2.22.1
		staticMAC1 OBJECT-TYPE
			SYNTAX Opaque (SIZE (8))
			ACCESS read-write
			STATUS mandatory
			DESCRIPTION
				"Static MAC entry 1"
			::= { staticMACTable 1 }

		
-- Static MAC Address entry 2
-- When reading data from this OID
-- ===============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Reserve
-- BIT[56]   - Use FID
--             (0) - Use MAC only to lookup in static table
--             (1) - Use (FID+MAC) to lookup in static table
-- BIT[57:60]- Filter VLAN ID, representing on of the 16 active VLANs
-- 
-- When writing data to this OID
-- ==============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Use FID
--             (0) - Use MAC only to lookup in static table
--             (1) - Use (FID+MAC) to lookup in static table
-- BIT[56:59]- Filter VLAN ID, representing on of the 16 active VLANs
		-- 1.3.6.1.4.1.11606.2.22.2
		staticMAC2 OBJECT-TYPE
			SYNTAX Opaque (SIZE (8))
			ACCESS read-write
			STATUS mandatory
			DESCRIPTION
				"Static MAC entry 2"
			::= { staticMACTable 2 }

		
-- Static MAC Address entry 3
-- When reading data from this OID
-- ===============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Reserve
-- BIT[56]   - Use FID
--             (0) - Use MAC only to lookup in static table
--             (1) - Use (FID+MAC) to lookup in static table
-- BIT[57:60]- Filter VLAN ID, representing on of the 16 active VLANs
-- 
-- When writing data to this OID
-- ==============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Use FID
--             (0) - Use MAC only to lookup in static table
--             (1) - Use (FID+MAC) to lookup in static table
-- BIT[56:59]- Filter VLAN ID, representing on of the 16 active VLANs
		-- 1.3.6.1.4.1.11606.2.22.3
		staticMAC3 OBJECT-TYPE
			SYNTAX Opaque (SIZE (8))
			ACCESS read-write
			STATUS mandatory
			DESCRIPTION
				"Static MAC entry 3"
			::= { staticMACTable 3 }

		
-- Static MAC Address entry 4
-- When reading data from this OID
-- ===============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Reserve
-- BIT[56]   - Use FID
--             (0) - Use MAC only to lookup in static table
--             (1) - Use (FID+MAC) to lookup in static table
-- BIT[57:60]- Filter VLAN ID, representing on of the 16 active VLANs
-- 
-- When writing data to this OID
-- ==============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Use FID
--             (0) - Use MAC only to lookup in static table
--             (1) - Use (FID+MAC) to lookup in static table
-- BIT[56:59]- Filter VLAN ID, representing on of the 16 active VLANs
		-- 1.3.6.1.4.1.11606.2.22.4
		staticMAC4 OBJECT-TYPE
			SYNTAX Opaque (SIZE (8))
			ACCESS read-write
			STATUS mandatory
			DESCRIPTION
				"Static MAC entry 4"
			::= { staticMACTable 4 }

		
-- Static MAC Address entry 5
-- When reading data from this OID
-- ===============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Reserve
-- BIT[56]   - Use FID
--             (0) - Use MAC only to lookup in static table
--             (1) - Use (FID+MAC) to lookup in static table
-- BIT[57:60]- Filter VLAN ID, representing on of the 16 active VLANs
-- 
-- When writing data to this OID
-- ==============================
-- BIT[0:47] - 48 bit MAC address
-- BIT[48:52]- Forwarding Ports. E.g.
--             "10000" - Forward to port1
--             "01000" - Forward to port2
--             "01100" - Forward to port2 and 3
-- BIT[53]   - Valid
--             (0) This entry is not valid
--             (1) This entry is valid, the lookup result will be used.
-- BIT[54]   - Override
--             (0) No override
--             (1) Override spanning tree "transmit enable = 0" 
--                 or "receive enable = 0" setting. This bit is 
--                 used for spanning tree implementation.
-- BIT[55]   - Use FID
--             (0) - Use MAC only to lookup in static table
--             (1) - Use (FID+MAC) to lookup in static table
-- BIT[56:59]- Filter VLAN ID, representing on of the 16 active VLANs
		-- 1.3.6.1.4.1.11606.2.22.5
		staticMAC5 OBJECT-TYPE
			SYNTAX Opaque (SIZE (8))
			ACCESS read-write
			STATUS mandatory
			DESCRIPTION
				"Static MAC entry 5"
			::= { staticMACTable 5 }

		
-- CPON-100 Dynamic MAC Table
		-- 1.3.6.1.4.1.11606.2.23
		dynamicMACTable OBJECT IDENTIFIER ::= { cpon100 23 }

		
-- Dynamic MAC entry in the table
		-- 1.3.6.1.4.1.11606.2.23.1
		macEntryCnt OBJECT-TYPE
			SYNTAX INTEGER (0..1024)
			ACCESS read-only
			STATUS mandatory
			DESCRIPTION
				"Dynamic MAC Entry Count"
			::= { dynamicMACTable 1 }

		
-- MAC entry to read
		-- 1.3.6.1.4.1.11606.2.23.2
		macEntryID OBJECT-TYPE
			SYNTAX INTEGER (0..1024)
			ACCESS read-write
			STATUS mandatory
			DESCRIPTION
				"Dynamic MAC Entry ID"
			::= { dynamicMACTable 2 }

		
-- The dynamic MAC entry based on "macEntryID" selected
		-- 1.3.6.1.4.1.11606.2.23.3
		macEntry OBJECT-TYPE
			SYNTAX Opaque (SIZE (8))
			ACCESS read-only
			STATUS mandatory
			DESCRIPTION
				"Dynamic MAC entry data"
			::= { dynamicMACTable 3 }

		
-- CPON-100  Customer Data Port 1 Control and Status
		-- 1.3.6.1.4.1.11606.2.24
		cpon100Port1 OBJECT IDENTIFIER ::= { cpon100 24 }

		
-- Link status:
-- (0) - Link not good
-- (1) - Link good
		-- 1.3.6.1.4.1.11606.2.24.1
		port1LinkStatus OBJECT-TYPE
			SYNTAX INTEGER (0..1)
			ACCESS read-only
			STATUS mandatory
			DESCRIPTION
				"Port1 Link Status"
			::= { cpon100Port1 1 }

		
-- MDI-X status:
-- (0) - MDI-X or Cross Over cable plugged in
-- (1) - MDI or Straight through cable plugged
		-- 1.3.6.1.4.1.11606.2.24.2
		port1MDIXStatus OBJECT-TYPE
			SYNTAX INTEGER (0..1)
			ACCESS read-only
			STATUS mandatory
			DESCRIPTION
				"Port1 MID-X Status"
			::= { cpon100Port1 2 }

		
-- Port Auto-negotiation status:
-- (0) - Auto negotiation not done
-- (1) - Auto negotiation done
		-- 1.3.6.1.4.1.11606.2.24.3
		port1AutoNegotiationStatus OBJECT-TYPE
			SYNTAX INTEGER (0..1)
			ACCESS read-only
			STATUS mandatory
			DESCRIPTION
				"Port1 Auto-Negotiation Status"
			::= { cpon100Port1 3 }

		
-- Link capability:
-- Bit0: (0) - Link partner not 10BT half-duplex capable
--       (1) - Link partner 10BT halft-duplex capable
-- Bit1: (0) - Link partner no 10BT full-duplex capable
--       (1) - Link partner 10BT full-duplex capable
-- Bit2: (0) - Link partner not 100BT half-duplex capble
--       (1) - LInk partner 100BT half-duplex capable
-- Bit3: (0) - Link partner not 100BT full-duplex capble
--       (1) - LInk partner 100BT full-duplex capable
		-- 1.3.6.1.4.1.11606.2.24.4
		port1LinkCapability OBJECT-TYPE
			SYNTAX INTEGER (0..15)
			ACCESS read-only
			STATUS mandatory
			DESCRIPTION
				"Link Capability"
			::= { cpon100Port1 4 }

		
-- Flow control capability:
-- (0) - Link partner flow control incapable
-- (1) - Link partner flow control capable
		-- 1.3.6.1.4.1.11606.2.24.5
		port1FlowCtrlCapability OBJECT-TYPE
			SYNTAX INTEGER (0..1)
			ACCESS read-only
			STATUS mandatory
			DESCRIPTION
				"Port1 Flow Control Capability"
			::= { cpon100Port1 5 }

		
-- Far end fault status:
-- (0) - No far end fault status detected.
-- (1) - Far end fault status detected.
		-- 1.3.6.1.4.1.11606.2.24.6
		port1FarEndFaultStatus OBJECT-TYPE
			SYNTAX INTEGER (0..1)
			ACCESS read-only
			STATUS mandatory
			DESCRIPTION
				"Port1 Far End Fault Status"
			::= { cpon100Port1 6 }

		
-- Rx Lo-priority(default) octet count including bad packets
		-- 1.3.6.1.4.1.11606.2.24.7
		port1RxLoPriorityByte OBJECT-TYPE
			SYNTAX Counter
			ACCESS read-only
			STATUS mandatory
			DESCRIPTION
				"Port1 Receive Low Priority Octet Counter"
			::= { cpon100Port1 7 }

		
-- Rx Hi-priority(default) octet count including bad packets
		-- 1.3.6.1.4.1.11606.2.24.8
		port1RxHiPriorityByte OBJECT-TYPE
			SYNTAX Counter
			ACCESS read-only
			STATUS mandatory
			DESCRIPTION
				"Port1 Receive High Priority Octet Counter"
			::= { cpon100Port1 8 }

		
-- Rx undersize packets with good CRC
		-- 1.3.6.1.4.1.11606.2.24.9
		port1UndersizePkt OBJECT-TYPE
			SYNTAX Counter
			ACCESS read-only
			STATUS mandatory
			DESCRIPTION
				"Port1 Undersize Packet Counter"
			::= { cpon100Port1 9 }

		
-- Rx packets longer than 1522 byte with either CRC errors,
-- alignment errors, or symbol errors ( depends on max packet size setting)
		-- 1.3.6.1.4.1.11606.2.24.12
		port1RxJabbers OBJECT-TYPE
			SYNTAX Counter
			ACCESS read-only
			STATUS mandatory
			DESCRIPTION
				"Port1 Receive Jabbers Counter"
			::= { cpon100Port1 12 }

		
-- Rx packet within (64, 1522) bytes with an integral number of bytes and a 
-- bad CRC (Upper limit depends on max packet size setting)
		-- 1.3.6.1.4.1.11606.2.24.14
		port1CRCError OBJECT-TYPE
			SYNTAX Counter
			ACCESS read-only
			STATUS mandatory
			DESCRIPTION
				"Port1 CRC Error Counter"
			::= { cpon100Port1 14 }

		
-- The number of PAUSE frames received by a port. 
-- PAUSE frame is qualified with EtherType (88-08h), 
-- DA, control opcode(00-01), data length (64bytes mine), 
-- and a valid CRC
		-- 1.3.6.1.4.1.11606.2.24.17
		port1RxPausePkts OBJECT-TYPE
			SYNTAX Counter
			ACCESS read-only
			STATUS mandatory
			DESCRIPTION
				"Port1 Receive Pause Packet Counter"
			::= { cpon100Port1 17 }

		
-- Rx good broadcast packets( not including errored broadcast packets 
-- or valid multicast packets).
		-- 1.3.6.1.4.1.11606.2.24.18
		port1Broadcast OBJECT-TYPE
			SYNTAX Counter
			ACCESS read-only
			STATUS mandatory
			DESCRIPTION
				"Port1 Good Broadcast Packet counter"
			::= { cpon100Port1 18 }

		
-- Rx good multicast packets (not including MAC control frames, 
-- errored multicast packets or valid broadcast packets)
		-- 1.3.6.1.4.1.11606.2.24.19
		port1RxMulticast OBJECT-TYPE
			SYNTAX Counter
			ACCESS read-only
			STATUS mandatory
			DESCRIPTION
				"Port1 Receive Good Multicast Packet Counter"
			::= { cpon100Port1 19 }

		
-- Rx good unicast packets.
		-- 1.3.6.1.4.1.11606.2.24.20
		port1RxUnicast OBJECT-TYPE
			SYNTAX Counter
			ACCESS read-only
			STATUS mandatory
			DESCRIPTION
				"Port1 Receive Unicast Counter"
			::= { cpon100Port1 20 }

		
-- Total Rx packets (bad packets included) that were 64 octets in length
		-- 1.3.6.1.4.1.11606.2.24.21
		port1Rx64Octets OBJECT-TYPE
			SYNTAX Counter
			ACCESS read-only
			STATUS mandatory
			DESCRIPTION
				"Port1 Receive 64Octets Counter"
			::= { cpon100Port1 21 }

		
-- Total Rx packets (bad packets included) that are between 65 and 127 
-- octets in length
		-- 1.3.6.1.4.1.11606.2.24.22
		port1Rx65to127Octets OBJECT-TYPE
			SYNTAX Counter
			ACCESS read-only
			STATUS mandatory
			DESCRIPTION
				"Port1 Receive 65 to 127 Octets Counter"
			::= { cpon100Port1 22 }

		
-- Total Rx packets (bad packets included) that are between 128 and 255 
-- octets in length
		-- 1.3.6.1.4.1.11606.2.24.23
		port1Rx128to255Octets OBJECT-TYPE
			SYNTAX Counter
			ACCESS read-only
			STATUS mandatory
			DESCRIPTION
				"Port1 Receive 128 to 255 Octets Counter"
			::= { cpon100Port1 23 }

		
-- Total Rx packets (bad packets included) that are between 256 and 511 
-- octets in length
		-- 1.3.6.1.4.1.11606.2.24.24
		port1Rx256to511Octets OBJECT-TYPE
			SYNTAX Counter
			ACCESS read-only
			STATUS mandatory
			DESCRIPTION
				"Port1 Receive 256 to 511 Octets Counter"
			::= { cpon100Port1 24 }

		
-- Total Rx packets (bad packets included) that are between 512 and 1023 
-- octets in length
		-- 1.3.6.1.4.1.11606.2.24.25
		port1Rx512to1023Octets OBJECT-TYPE
			SYNTAX Counter
			ACCESS read-only
			STATUS mandatory
			DESCRIPTION
				"Port1 Receive 512 to 1023 Octets Counter"
			::= { cpon100Port1 25 }

		
-- Total Rx packets (bad packets included) that are between 1024 and 1522
-- octets in length (Upper limit depends on max packet size setting)
		-- 1.3.6.1.4.1.11606.2.24.26
		port1Rx1024to1522Octets OBJECT-TYPE
			SYNTAX Counter
			ACCESS read-only
			STATUS mandatory
			DESCRIPTION
				"Port1 Receive 1024 to 1522 Octets Counter"
			::= { cpon100Port1 26 }

		
-- Tx Lo-priority good octet count, ncluding PAUSE packets.
		-- 1.3.6.1.4.1.11606.2.24.27
		port1TxLoPriorityByte OBJECT-TYPE
			SYNTAX Counter
			ACCESS read-only
			STATUS mandatory
			DESCRIPTION
				"Port1 Transmit Low Priority Good Octet Counter"
			::= { cpon100Port1 27 }

		
-- Tx Hi-priority good octet count, ncluding PAUSE packets.
		-- 1.3.6.1.4.1.11606.2.24.28
		port1TxHiPriorityByte OBJECT-TYPE
			SYNTAX Counter
			ACCESS read-only
			STATUS mandatory
			DESCRIPTION
				"Port1 Transmit High Priority Good Octet Counter"
			::= { cpon100Port1 28 }

		
-- The number of PAUSE frames transmitted by a port
		-- 1.3.6.1.4.1.11606.2.24.30
		port1PausePkts OBJECT-TYPE
			SYNTAX Counter
			ACCESS read-only
			STATUS mandatory
			DESCRIPTION
				"Port1 Pause Packet Counter"
			::= { cpon100Port1 30 }

		
-- Tx good broadcast packets (not including errored broadcast or valid 
-- multicast packets)
		-- 1.3.6.1.4.1.11606.2.24.31
		port1TxBroadcastPkts OBJECT-TYPE
			SYNTAX Counter
			ACCESS read-only
			STATUS mandatory
			DESCRIPTION
				"Port1 Transmit Good Broadcast Packet Counter"
			::= { cpon100Port1 31 }

		
-- Tx good broadcast packets (not including errored broadcast or 
-- valid multicast packets)
		-- 1.3.6.1.4.1.11606.2.24.32
		port1TxMulticastPkts OBJECT-TYPE
			SYNTAX Counter
			ACCESS read-only
			STATUS mandatory
			DESCRIPTION
				"Port1 Transmit Good Multicast Packet Counter"
			::= { cpon100Port1 32 }

		
-- Tx good unicast packets.
		-- 1.3.6.1.4.1.11606.2.24.33
		port1TxUnicastPkts OBJECT-TYPE
			SYNTAX Counter
			ACCESS read-only
			STATUS mandatory
			DESCRIPTION
				"Port1 Transmit Good Unicast Packet Counter"
			::= { cpon100Port1 33 }

		
-- Tx total collision, half-duplex only
		-- 1.3.6.1.4.1.11606.2.24.35
		port1TxTotalCollision OBJECT-TYPE
			SYNTAX Counter
			ACCESS read-only
			STATUS mandatory
			DESCRIPTION
				"Port1 Transmit Total Collision Packet Counter for half-duplex only"
			::= { cpon100Port1 35 }

		
-- Tx packets dropped due to lack of resources
		-- 1.3.6.1.4.1.11606.2.24.39
		port1TxDroppedPkts OBJECT-TYPE
			SYNTAX Counter
			ACCESS read-only
			STATUS mandatory
			DESCRIPTION
				"Port1 Transmit Drop Packet Counter"
			::= { cpon100Port1 39 }

		
-- Rx packets dropped due to lack of resources
		-- 1.3.6.1.4.1.11606.2.24.40
		port1RxDroppedPkts OBJECT-TYPE
			SYNTAX Counter
			ACCESS read-only
			STATUS mandatory
			DESCRIPTION
				"Port1 Receive Drop Packet Counter"
			::= { cpon100Port1 40 }

		
-- CPON-100 Control table for Port 1
		-- 1.3.6.1.4.1.11606.2.24.45
		cpon100Port1Ctrl OBJECT IDENTIFIER ::= { cpon100Port1 45 }
-- Port1 Controls
		
-- DiffServ priority enable:
-- (0) - Disable DiffServ function. 
-- (1) - Enable DiffServ priority classification for ingress.
-- NOTE: "DiffServ", "802.1p" and port priority can be enabled at the same time
		-- 1.3.6.1.4.1.11606.2.24.45.1
		port1CtrlDiffServPriority OBJECT-TYPE
			SYNTAX INTEGER (0..1)
			ACCESS read-write
			STATUS mandatory
			DESCRIPTION
				"Port1 DiffServe Priority Control"
			::= { cpon100Port1Ctrl 1 }

		
-- 802.1p priority classification enable:
-- (0) - Disable 802.1p
-- (1) - Enable 802.1p priority classification for ingress
		-- 1.3.6.1.4.1.11606.2.24.45.2
		port1Ctrl802dot1pPriorityClass OBJECT-TYPE
			SYNTAX INTEGER (0..1)
			ACCESS read-write
			STATUS mandatory
			DESCRIPTION
				"Port1 802.1p Priority Class Enable"
			::= { cpon100Port1Ctrl 2 }

		
-- Port-based priority classification enable:
-- (0) - Ingress packets on port will be classified as low priority 
--       if "DiffSev" or "802.1p" classification is not enabled or 
--       fails to classify.
-- (1) - Ingress packets on the port will be classified as high priority
--       if "DiffServ" or "802.1p" classification is not enabled or fails
--       to classify.
		-- 1.3.6.1.4.1.11606.2.24.45.3
		port1CtrlPortBasedPriority OBJECT-TYPE
			SYNTAX INTEGER (0..1)
			ACCESS read-write
			STATUS mandatory
			DESCRIPTION
				"Port1 Port Based Priority"
			::= { cpon100Port1Ctrl 3 }

		
-- Priority enable:
-- (0) - Single output queue on the port. There is no priority 
--       differentiation even though packets are classified into 
--       high or low priority.
-- (1) - The port output queue is split into high and low priority queues.
		-- 1.3.6.1.4.1.11606.2.24.45.4
		port1CtrlPriorityCtrl OBJECT-TYPE
			SYNTAX INTEGER (0..1)
			ACCESS read-write
			STATUS mandatory
			DESCRIPTION
				"Port1 Priority Enable"
			::= { cpon100Port1Ctrl 4 }

		
-- Auto-Negotiation:
-- (0) - Auto-Negotiation is on
-- (1) - Disable auto-negotiation, speed and duplex are decided by bit 6 
--       and 5 of the same register.
		-- 1.3.6.1.4.1.11606.2.24.45.5
		port1CtrlAutoNegotiation OBJECT-TYPE
			SYNTAX INTEGER (0..1)
			ACCESS read-write
			STATUS mandatory
			DESCRIPTION
				"Port1 Auto-Negotiation Enable"
			::= { cpon100Port1Ctrl 5 }

		
-- Force full-Duplex:
-- (0) - Forced half-duplex if Auto-negotation is disabled or
--       Auto-negotiation is enabled but failed
-- (1) - Forced full duplex if Auto-negotiation is disabled or
--       Auto-negotiation is enabled but failed.
		-- 1.3.6.1.4.1.11606.2.24.45.6
		port1CtrlForceFullDuplex OBJECT-TYPE
			SYNTAX INTEGER (0..1)
			ACCESS read-write
			STATUS mandatory
			DESCRIPTION
				"Port1 Force Full-duplex"
			::= { cpon100Port1Ctrl 6 }

		
-- Broadcast storm protection enable:
-- (0) - Disable broadast storm protection
-- (1) - Enable broadcast storm protection for ingress packets
		-- 1.3.6.1.4.1.11606.2.24.45.7
		port1CtrlBroadcastStormProtection OBJECT-TYPE
			SYNTAX INTEGER (0..1)
			ACCESS read-write
			STATUS mandatory
			DESCRIPTION
				"Port1 Broadcast Storm Protection"
			::= { cpon100Port1Ctrl 7 }

		
-- Force flow control:
-- (0) - The flow control is enabled based on Auto-Negotiation result.
--       NOTE: Setting a port for both half-duplex and forced flow 
--             control is an illegal configuration. For half-duplex 
--             enable back pressure.
-- (1) - Will always enable RX and TX flow control on the port, 
--       regardless of Auto-Negotiation result.
		-- 1.3.6.1.4.1.11606.2.24.45.8
		port1CtrlForceFlowCtrl OBJECT-TYPE
			SYNTAX INTEGER (0..1)
			ACCESS read-write
			STATUS mandatory
			DESCRIPTION
				"Port1 Force Flow Control"
			::= { cpon100Port1Ctrl 8 }

		
-- Back pressure enable:
-- (0) - Disable ports's half-duplex back pressure
-- (1) - Enable ports's half-duplex back pressure
		-- 1.3.6.1.4.1.11606.2.24.45.9
		port1CtrlBackPressure OBJECT-TYPE
			SYNTAX INTEGER (0..1)
			ACCESS read-write
			STATUS mandatory
			DESCRIPTION
				"Port1 Backpressure Enable"
			::= { cpon100Port1Ctrl 9 }

		
-- Transmit enable:
-- (0) - Disable packet transmission on the port.
-- (1) - Enable packet transmission on the port.
		-- 1.3.6.1.4.1.11606.2.24.45.10
		port1CtrlTxEnable OBJECT-TYPE
			SYNTAX INTEGER (0..1)
			ACCESS read-write
			STATUS mandatory
			DESCRIPTION
				"Port1 Transmit Enable"
			::= { cpon100Port1Ctrl 10 }

		
-- Receive enable:
-- (0) - Disable packet reception on the port.
-- (1) - Enable packet reception on the port.
		-- 1.3.6.1.4.1.11606.2.24.45.11
		port1CtrlRxEnable OBJECT-TYPE
			SYNTAX INTEGER (0..1)
			ACCESS read-write
			STATUS mandatory
			DESCRIPTION
				"Port1 Receive Enable"
			::= { cpon100Port1Ctrl 11 }

		
-- Port Power Down:
-- (0) - Normal operation
-- (1) - Power down
		-- 1.3.6.1.4.1.11606.2.24.45.12
		port1CtrlPowerDown OBJECT-TYPE
			SYNTAX INTEGER (0..1)
			ACCESS read-write
			STATUS mandatory
			DESCRIPTION
				"Port1 Port Powerdown"
			::= { cpon100Port1Ctrl 12 }

		
-- MAC loopback test:
-- (0) - Normal operation
-- (1) - Perform MAC loopback test
		-- 1.3.6.1.4.1.11606.2.24.45.13
		port1CtrlMACLoopBackTest OBJECT-TYPE
			SYNTAX INTEGER (0..1)
			ACCESS read-write
			STATUS mandatory
			DESCRIPTION
				"Port1 MAC Loopback Test"
			::= { cpon100Port1Ctrl 13 }

		
-- PHY loopback test:
-- (0) - Normal operation
-- (1) - Perform PHY loopback test, i.e. loopback MAC's Tx back to Rx
		-- 1.3.6.1.4.1.11606.2.24.45.14
		port1CtrlPHYLoopbackTest OBJECT-TYPE
			SYNTAX INTEGER (0..1)
			ACCESS read-write
			STATUS mandatory
			DESCRIPTION
				"Port1 PHY Loopback Test"
			::= { cpon100Port1Ctrl 14 }

		
-- Remote loopback test:
-- (0) - Normal operation
-- (1) - Perform remote loopback test, i.e. loopback PHY's Tx back to Rx
		-- 1.3.6.1.4.1.11606.2.24.45.15
		port1CtrlRemoteLoopbackTest OBJECT-TYPE
			SYNTAX INTEGER (0..1)
			ACCESS read-write
			STATUS mandatory
			DESCRIPTION
				"Port1 Remote Loopback Test"
			::= { cpon100Port1Ctrl 15 }

		
-- Tag Insertion and Tag removal:
-- (0) - Disable both tag removal and tag insertion 
-- 
-- (1) - When packets are output on the port, the switch will remove 
--       802.1q tags from packets with 802.1q tags when received. 
--       The switch will not add tags to packets already tagged. 
--       The tag inserted is the ingress ports's "port VID." 
--       and
--       Disable tag insertion.
-- 
-- (2) - Disable tag removal 
--       and
--       When packets are output on the port, the switch will add 
--       802.1q tags to packets without 802.1q tags when received. 
--       The switch will not add tags to packets already tagged. 
--       The tag inserted is the ingress port's "port VID".
-- 
-- (3) - When packets are output on the port, the switch will remove 
--       802.1q tags from packets with 802.1q tags when received. 
--       The switch will not add tags to packets already tagged. 
--       The tag inserted is the ingress ports's "port VID." 
--       and
--       When packets are output on the port, the switch will add 
--       802.1q tags to packets without 802.1q tags when received. 
--       The switch will not add tags to packets already tagged. 
--       The tag inserted is the ingress port's "port VID".
		-- 1.3.6.1.4.1.11606.2.24.45.16
		port1CtrlTagInsertionRemoval OBJECT-TYPE
			SYNTAX INTEGER (0..3)
			ACCESS read-write
			STATUS mandatory
			DESCRIPTION
				"Port1 Tag Insertion/Tag Removal"
			::= { cpon100Port1Ctrl 16 }

		
-- Port based VLAN:
-- Define the port's "Port VLAN membership." Bit 4 stands 
-- for port 5, bit 3 for port 4...bit 0 for port1. The port
-- can only communicate within the membership. A '1' includes 
-- a port in the membership, a '0' excludes a port from membership.
		-- 1.3.6.1.4.1.11606.2.24.45.17
		port1CtrlPortMembership OBJECT-TYPE
			SYNTAX INTEGER (0..31)
			ACCESS read-write
			STATUS mandatory
			DESCRIPTION
				"Port1 Port Membership"
			::= { cpon100Port1Ctrl 17 }

		
-- Ingress VLAN filtering:
-- (0) - No ingress VLAN filtering.
-- (1) - The switch will discard packets whose VID port membership  
--       in VLAN table bit[20:16] does not include the ingress port.
		-- 1.3.6.1.4.1.11606.2.24.45.18
		port1CtrlIngressVLANFiltering OBJECT-TYPE
			SYNTAX INTEGER (0..1)
			ACCESS read-write
			STATUS mandatory
			DESCRIPTION
				"Port1 Ingress VLAN Filtering"
			::= { cpon100Port1Ctrl 18 }

		
-- Discard Non-PVID packet:
-- (0) - No packets will be discarded.
-- (1) - The switch will discard packets whose VID does not 
--       match ingress port default VID.
		-- 1.3.6.1.4.1.11606.2.24.45.19
		port1CtrlDiscardNon-PVIDPkt OBJECT-TYPE
			SYNTAX INTEGER (0..1)
			ACCESS read-write
			STATUS mandatory
			DESCRIPTION
				"Port1 Discard Non-PVID Packet"
			::= { cpon100Port1Ctrl 19 }

		
-- Default Tag:
-- This is a 16bit data for Port's default tag, containing:
-- Bit        Description:
-- =======================
-- 0..11   -  VID
-- 12      -  CFG bit
-- 13..15  -  User priority bits
		-- 1.3.6.1.4.1.11606.2.24.45.20
		port1CtrlDefaultTag OBJECT-TYPE
			SYNTAX INTEGER (0..65536)
			ACCESS read-write
			STATUS mandatory
			DESCRIPTION
				"Port1 Default Tag"
			::= { cpon100Port1Ctrl 20 }

		
-- Force speed:
-- (0) - Forced 10BT if Auto-Negotiation is disabled
-- (1) - Forced 100BT if Auto-Negotiation is disabled
		-- 1.3.6.1.4.1.11606.2.24.45.21
		port1CtrlForceSpeed OBJECT-TYPE
			SYNTAX INTEGER (0..1)
			ACCESS read-write
			STATUS mandatory
			DESCRIPTION
				"Port1 Force Speed"
			::= { cpon100Port1Ctrl 21 }

		
-- CPON-100 Customer Data Port 2 Control and Status
		-- 1.3.6.1.4.1.11606.2.25
		cpon100Port2 OBJECT IDENTIFIER ::= { cpon100 25 }

		
-- Link status:
-- (0) - Link not good
-- (1) - Link good
		-- 1.3.6.1.4.1.11606.2.25.1
		port2LinkStatus OBJECT-TYPE
			SYNTAX INTEGER (0..1)
			ACCESS read-only
			STATUS mandatory
			DESCRIPTION
				"Port2 Link Status"
			::= { cpon100Port2 1 }

		
-- MDI-X status:
-- (0) - MDI-X or Cross Over cable plugged in
-- (1) - MDI or Straight through cable plugged
		-- 1.3.6.1.4.1.11606.2.25.2
		port2MDIXStatus OBJECT-TYPE
			SYNTAX INTEGER (0..1)
			ACCESS read-only
			STATUS mandatory
			DESCRIPTION
				"Port2 MDI-X Status"
			::= { cpon100Port2 2 }

		
-- Port Auto-negotiation status:
-- (0) - Auto negotiation not done
-- (1) - Auto negotiation done
		-- 1.3.6.1.4.1.11606.2.25.3
		port2AutoNegotiationStatus OBJECT-TYPE
			SYNTAX INTEGER (0..1)
			ACCESS read-only
			STATUS mandatory
			DESCRIPTION
				"Port2 Auto-Negotiation Status"
			::= { cpon100Port2 3 }

		
-- Link capability:
-- Bit0: (0) - Link partner not 10BT half-duplex capable
--       (1) - Link partner 10BT halft-duplex capable
-- Bit1: (0) - Link partner no 10BT full-duplex capable
--       (1) - Link partner 10BT full-duplex capable
-- Bit2: (0) - Link partner not 100BT half-duplex capble
--       (1) - LInk partner 100BT half-duplex capable
-- Bit3: (0) - Link partner not 100BT full-duplex capble
--       (1) - LInk partner 100BT full-duplex capable
		-- 1.3.6.1.4.1.11606.2.25.4
		port2LinkCapability OBJECT-TYPE
			SYNTAX INTEGER (0..15)
			ACCESS read-only
			STATUS mandatory
			DESCRIPTION
				"Port2 Link Capability"
			::= { cpon100Port2 4 }

		
-- Flow control capability:
-- (0) - Link partner flow control incapable
-- (1) - Link partner flow control capable
		-- 1.3.6.1.4.1.11606.2.25.5
		port2FlowCtrlCapability OBJECT-TYPE
			SYNTAX INTEGER (0..1)
			ACCESS read-only
			STATUS mandatory
			DESCRIPTION
				"Port2 Flow Control Capability"
			::= { cpon100Port2 5 }

		
-- Far end fault status:
-- (0) - No far end fault status detected.
-- (1) - Far end fault status detected.
		-- 1.3.6.1.4.1.11606.2.25.6
		port2FarEndFaultStatus OBJECT-TYPE
			SYNTAX INTEGER (0..1)
			ACCESS read-only
			STATUS mandatory
			DESCRIPTION
				"Port2 Far End Fault Status"
			::= { cpon100Port2 6 }

		
-- Rx Lo-priority(default) octet count including bad packets
		-- 1.3.6.1.4.1.11606.2.25.7
		port2RxLoPriorityByte OBJECT-TYPE
			SYNTAX Counter
			ACCESS read-only
			STATUS mandatory
			DESCRIPTION
				"Port2 Receive Low Priority Octet Counter"
			::= { cpon100Port2 7 }

		
-- Rx Hi-priority(default) octet count including bad packets
		-- 1.3.6.1.4.1.11606.2.25.8
		port2RxHiPriorityByte OBJECT-TYPE
			SYNTAX Counter
			ACCESS read-only
			STATUS mandatory
			DESCRIPTION
				"Port2 Receive High Priority Octet Counter"
			::= { cpon100Port2 8 }

		
-- Rx undersize packets with good CRC
		-- 1.3.6.1.4.1.11606.2.25.9
		port2UndersizePkt OBJECT-TYPE
			SYNTAX Counter
			ACCESS read-only
			STATUS mandatory
			DESCRIPTION
				"Port2 Undersize Packet Counter"
			::= { cpon100Port2 9 }

		
-- Rx packets longer than 1522 byte with either CRC errors,
-- alignment errors, or symbol errors ( depends on max packet size setting)
		-- 1.3.6.1.4.1.11606.2.25.12
		port2RxJabbers OBJECT-TYPE
			SYNTAX Counter
			ACCESS read-only
			STATUS mandatory
			DESCRIPTION
				"Port2 Receive Jabbers Counter"
			::= { cpon100Port2 12 }

		
-- Rx packet within (64, 1522) bytes with an integral number of bytes and a 
-- bad CRC (Upper limit depends on max packet size setting)
		-- 1.3.6.1.4.1.11606.2.25.14
		port2CRCError OBJECT-TYPE
			SYNTAX Counter
			ACCESS read-only
			STATUS mandatory
			DESCRIPTION
				"Port2 CRC Error Counter"
			::= { cpon100Port2 14 }

		
-- The number of PAUSE frames received by a port. 
-- PAUSE frame is qualified with EtherType (88-08h), 
-- DA, control opcode(00-01), data length (64bytes mine), 
-- and a valid CRC
		-- 1.3.6.1.4.1.11606.2.25.17
		port2RxPausePkts OBJECT-TYPE
			SYNTAX Counter
			ACCESS read-only
			STATUS mandatory
			DESCRIPTION
				"Port2 Receive Pause Packet Counter"
			::= { cpon100Port2 17 }

		
-- Rx good broadcast packets( not including errored broadcast packets 
-- or valid multicast packets).
		-- 1.3.6.1.4.1.11606.2.25.18
		port2Broadcast OBJECT-TYPE
			SYNTAX Counter
			ACCESS read-only
			STATUS mandatory
			DESCRIPTION
				"Port2 Broadcast Good Packet Counter"
			::= { cpon100Port2 18 }

		
-- Rx good multicast packets (not including MAC control frames, 
-- errored multicast packets or valid broadcast packets)
		-- 1.3.6.1.4.1.11606.2.25.19
		port2RxMulticast OBJECT-TYPE
			SYNTAX Counter
			ACCESS read-only
			STATUS mandatory
			DESCRIPTION
				"Port2 Receive Multicast Good Packet Counter"
			::= { cpon100Port2 19 }

		
-- Rx good unicast packets.
		-- 1.3.6.1.4.1.11606.2.25.20
		port2RxUnicast OBJECT-TYPE
			SYNTAX Counter
			ACCESS read-only
			STATUS mandatory
			DESCRIPTION
				"Port2 Receive Unicast Counter"
			::= { cpon100Port2 20 }

		
-- Total Rx packets (bad packets included) that were 64 octets in length
		-- 1.3.6.1.4.1.11606.2.25.21
		port2Rx64Octets OBJECT-TYPE
			SYNTAX Counter
			ACCESS read-only
			STATUS mandatory
			DESCRIPTION
				"Port2 Receive 64 Octets Counter"
			::= { cpon100Port2 21 }

		
-- Total Rx packets (bad packets included) that are between 65 and 127 
-- octets in length
		-- 1.3.6.1.4.1.11606.2.25.22
		port2Rx65to127Octets OBJECT-TYPE
			SYNTAX Counter
			ACCESS read-only
			STATUS mandatory
			DESCRIPTION
				"Port2 Receive 65 to 127 Octets Counter"
			::= { cpon100Port2 22 }

		
-- Total Rx packets (bad packets included) that are between 128 and 255 
-- octets in length
		-- 1.3.6.1.4.1.11606.2.25.23
		port2Rx128to255Octets OBJECT-TYPE
			SYNTAX Counter
			ACCESS read-only
			STATUS mandatory
			DESCRIPTION
				"Port2 Receive 128 to 255 Octets Counter"
			::= { cpon100Port2 23 }

		
-- Total Rx packets (bad packets included) that are between 256 and 511 
-- octets in length
		-- 1.3.6.1.4.1.11606.2.25.24
		port2Rx256to511Octets OBJECT-TYPE
			SYNTAX Counter
			ACCESS read-only
			STATUS mandatory
			DESCRIPTION
				"Port2 Receive 256 to 511 Octets Counter"
			::= { cpon100Port2 24 }

		
-- Total Rx packets (bad packets included) that are between 512 and 1023 
-- octets in length
		-- 1.3.6.1.4.1.11606.2.25.25
		port2Rx512to1023Octets OBJECT-TYPE
			SYNTAX Counter
			ACCESS read-only
			STATUS mandatory
			DESCRIPTION
				"Port2 Receive 512 to 1023 Octets Counter"
			::= { cpon100Port2 25 }

		
-- Total Rx packets (bad packets included) that are between 1024 and 1522
-- octets in length (Upper limit depends on max packet size setting)
		-- 1.3.6.1.4.1.11606.2.25.26
		port2Rx1024to1522Octets OBJECT-TYPE
			SYNTAX Counter
			ACCESS read-only
			STATUS mandatory
			DESCRIPTION
				"Port2 Receive 1024 to 1522 Octets Counter"
			::= { cpon100Port2 26 }

		
-- Tx Lo-priority good octet count, ncluding PAUSE packets.
		-- 1.3.6.1.4.1.11606.2.25.27
		port2TxLoPriorityByte OBJECT-TYPE
			SYNTAX Counter
			ACCESS read-only
			STATUS mandatory
			DESCRIPTION
				"Port2 Transmit Low Priority Packet Counter"
			::= { cpon100Port2 27 }

		
-- Tx Hi-priority good octet count, ncluding PAUSE packets.
		-- 1.3.6.1.4.1.11606.2.25.28
		port2TxHiPriorityByte OBJECT-TYPE
			SYNTAX Counter
			ACCESS read-only
			STATUS mandatory
			DESCRIPTION
				"Port2 Transmit High Priority Packet Counter"
			::= { cpon100Port2 28 }

		
-- The number of PAUSE frames transmitted by a port
		-- 1.3.6.1.4.1.11606.2.25.30
		port2PausePkts OBJECT-TYPE
			SYNTAX Counter
			ACCESS read-only
			STATUS mandatory
			DESCRIPTION
				"Port2 Pause Packet Counter"
			::= { cpon100Port2 30 }

		
-- Tx good broadcast packets (not including errored broadcast or valid 
-- multicast packets)
		-- 1.3.6.1.4.1.11606.2.25.31
		port2TxBroadcastPkts OBJECT-TYPE
			SYNTAX Counter
			ACCESS read-only
			STATUS mandatory
			DESCRIPTION
				"Port2 Transmit Broadcast Packet Counter"
			::= { cpon100Port2 31 }

		
-- Tx good broadcast packets (not including errored broadcast or 
-- valid multicast packets)
		-- 1.3.6.1.4.1.11606.2.25.32
		port2TxMulticastPkts OBJECT-TYPE
			SYNTAX Counter
			ACCESS read-only
			STATUS mandatory
			DESCRIPTION
				"Port2 Transmit Multicast Packet Counter"
			::= { cpon100Port2 32 }

		
-- Tx good unicast packets.
		-- 1.3.6.1.4.1.11606.2.25.33
		port2TxUnicastPkts OBJECT-TYPE
			SYNTAX Counter
			ACCESS read-only
			STATUS mandatory
			DESCRIPTION
				"Port2 Transmit Unicast Packet Counter"
			::= { cpon100Port2 33 }

		
-- Tx total collision, half-duplex only
		-- 1.3.6.1.4.1.11606.2.25.35
		port2TxTotalCollision OBJECT-TYPE
			SYNTAX Counter
			ACCESS read-only
			STATUS mandatory
			DESCRIPTION
				"Port2 Transmit Total Collision Packet Counter"
			::= { cpon100Port2 35 }

		
-- Tx packets dropped due to lack of resources
		-- 1.3.6.1.4.1.11606.2.25.39
		port2TxDroppedPkts OBJECT-TYPE
			SYNTAX Counter
			ACCESS read-only
			STATUS mandatory
			DESCRIPTION
				"Port2 Transmit Dropped Packet Counter"
			::= { cpon100Port2 39 }

		
-- Rx packets dropped due to lack of resources
		-- 1.3.6.1.4.1.11606.2.25.40
		port2RxDroppedPkts OBJECT-TYPE
			SYNTAX Counter
			ACCESS read-only
			STATUS mandatory
			DESCRIPTION
				"Port2 Receive Dropped Packet Counter"
			::= { cpon100Port2 40 }

		
-- CPON-100 Control table for Port 2
		-- 1.3.6.1.4.1.11606.2.25.45
		port2Ctrl OBJECT IDENTIFIER ::= { cpon100Port2 45 }
-- Port2 Controls
		
-- DiffServ priority enable:
-- (0) - Disable DiffServ function. 
-- (1) - Enable DiffServ priority classification for ingress.
-- NOTE: "DiffServ", "802.1p" and port priority can be enabled at the same time
		-- 1.3.6.1.4.1.11606.2.25.45.1
		port2CtrlDiffServPriority OBJECT-TYPE
			SYNTAX INTEGER (0..1)
			ACCESS read-write
			STATUS mandatory
			DESCRIPTION
				"Port2 DiffServe Priority Control"
			::= { port2Ctrl 1 }

		
-- 802.1p priority classification enable:
-- (0) - Disable 802.1p
-- (1) - Enable 802.1p priority classification for ingress
		-- 1.3.6.1.4.1.11606.2.25.45.2
		port2Ctrl802dot1pPriorityClass OBJECT-TYPE
			SYNTAX INTEGER (0..1)
			ACCESS read-write
			STATUS mandatory
			DESCRIPTION
				"Port2 802.1p Priority Class Enable"
			::= { port2Ctrl 2 }

		
-- Port-based priority classification enable:
-- (0) - Ingress packets on port will be classified as low priority 
--       if "DiffSev" or "802.1p" classification is not enabled or 
--       fails to classify.
-- (1) - Ingress packets on the port will be classified as high priority
--       if "DiffServ" or "802.1p" classification is not enabled or fails
--       to classify.
		-- 1.3.6.1.4.1.11606.2.25.45.3
		port2CtrlPortBasedPriority OBJECT-TYPE
			SYNTAX INTEGER (0..1)
			ACCESS read-write
			STATUS mandatory
			DESCRIPTION
				"Port2 802.1p Priority Class Enable"
			::= { port2Ctrl 3 }

		
-- Priority enable:
-- (0) - Single output queue on the port. There is no priority 
--       differentiation even though packets are classified into 
--       high or low priority.
-- (1) - The port output queue is split into high and low priority queues.
		-- 1.3.6.1.4.1.11606.2.25.45.4
		port2CtrlPriorityCtrl OBJECT-TYPE
			SYNTAX INTEGER (0..1)
			ACCESS read-write
			STATUS mandatory
			DESCRIPTION
				"Port2 Priority Enable"
			::= { port2Ctrl 4 }

		
-- Auto-Negotiation:
-- (0) - Auto-Negotiation is on
-- (1) - Disable auto-negotiation, speed and duplex are decided by bit 6 
--       and 5 of the same register.
		-- 1.3.6.1.4.1.11606.2.25.45.5
		port2CtrlAutoNegotiation OBJECT-TYPE
			SYNTAX INTEGER (0..1)
			ACCESS read-write
			STATUS mandatory
			DESCRIPTION
				"Port2 Auto-Negotiation Enable"
			::= { port2Ctrl 5 }

		
-- Forced full-Duplex:
-- (0) - Forced half-duplex if Auto-negotation is disabled or
--       Auto-negotiation is enabled but failed
-- (1) - Forced full duplex if Auto-negotiation is disabled or
--       Auto-negotiation is enabled but failed.
		-- 1.3.6.1.4.1.11606.2.25.45.6
		port2CtrlForcedFullDuplex OBJECT-TYPE
			SYNTAX INTEGER (0..1)
			ACCESS read-write
			STATUS mandatory
			DESCRIPTION
				"Port2 Force Full-duplex"
			::= { port2Ctrl 6 }

		
-- Broadcast storm protection enable:
-- (0) - Disable broadast storm protection
-- (1) - Enable broadcast storm protection for ingress packets
		-- 1.3.6.1.4.1.11606.2.25.45.7
		port2CtrlBroadcastStormProtection OBJECT-TYPE
			SYNTAX INTEGER (0..1)
			ACCESS read-write
			STATUS mandatory
			DESCRIPTION
				"Port2 Broadcast Storm Protection Enable"
			::= { port2Ctrl 7 }

		
-- Force flow control:
-- (0) - The flow control is enabled based on Auto-Negotiation result.
--       NOTE: Setting a port for both half-duplex and forced flow 
--             control is an illegal configuration. For half-duplex 
--             enable back pressure.
-- (1) - Will always enable RX and TX flow control on the port, 
--       regardless of Auto-Negotiation result.
		-- 1.3.6.1.4.1.11606.2.25.45.8
		port2CtrlForceFlowCtrl OBJECT-TYPE
			SYNTAX INTEGER (0..1)
			ACCESS read-write
			STATUS mandatory
			DESCRIPTION
				"Port2 Force Flow Control"
			::= { port2Ctrl 8 }

		
-- Back pressure enable:
-- (0) - Disable ports's half-duplex back pressure
-- (1) - Enable ports's half-duplex back pressure
		-- 1.3.6.1.4.1.11606.2.25.45.9
		port2CtrlBackPressure OBJECT-TYPE
			SYNTAX INTEGER (0..1)
			ACCESS read-write
			STATUS mandatory
			DESCRIPTION
				"Port2 Back Pressure Enable"
			::= { port2Ctrl 9 }

		
-- Transmit enable:
-- (0) - Disable packet transmission on the port.
-- (1) - Enable packet transmission on the port.
		-- 1.3.6.1.4.1.11606.2.25.45.10
		port2CtrlTxEnable OBJECT-TYPE
			SYNTAX INTEGER (0..1)
			ACCESS read-write
			STATUS mandatory
			DESCRIPTION
				"Port2 Transmit Enable"
			::= { port2Ctrl 10 }

		
-- Receive enable:
-- (0) - Disable packet reception on the port.
-- (1) - Enable packet reception on the port.
		-- 1.3.6.1.4.1.11606.2.25.45.11
		port2CtrlRxEnable OBJECT-TYPE
			SYNTAX INTEGER (0..1)
			ACCESS read-write
			STATUS mandatory
			DESCRIPTION
				"Port2 Receive Enable"
			::= { port2Ctrl 11 }

		
-- Port Power Down:
-- (0) - Normal operation
-- (1) - Power down
		-- 1.3.6.1.4.1.11606.2.25.45.12
		port2CtrlPowerDown OBJECT-TYPE
			SYNTAX INTEGER (0..1)
			ACCESS read-write
			STATUS mandatory
			DESCRIPTION
				"Port2 Powerdown"
			::= { port2Ctrl 12 }

		
-- MAC loopback test:
-- (0) - Normal operation
-- (1) - Perform MAC loopback test
		-- 1.3.6.1.4.1.11606.2.25.45.13
		port2CtrlMACLoopBackTest OBJECT-TYPE
			SYNTAX INTEGER (0..1)
			ACCESS read-write
			STATUS mandatory
			DESCRIPTION
				"Port2 MAC Loopback Test"
			::= { port2Ctrl 13 }

		
-- PHY loopback test:
-- (0) - Normal operation
-- (1) - Perform PHY loopback test, i.e. loopback MAC's Tx back to Rx
		-- 1.3.6.1.4.1.11606.2.25.45.14
		port2CtrlPHYLoopbackTest OBJECT-TYPE
			SYNTAX INTEGER (0..1)
			ACCESS read-write
			STATUS mandatory
			DESCRIPTION
				"Port2 PHY Loopback Test"
			::= { port2Ctrl 14 }

		
-- Remote loopback test:
-- (0) - Normal operation
-- (1) - Perform remote loopback test, i.e. loopback PHY's Tx back to Rx
		-- 1.3.6.1.4.1.11606.2.25.45.15
		port2CtrlRemoteLoopbackTest OBJECT-TYPE
			SYNTAX INTEGER (0..1)
			ACCESS read-write
			STATUS mandatory
			DESCRIPTION
				"Port2 Remote Loopback Test"
			::= { port2Ctrl 15 }

		
-- Tag Insertion and Tag removal:
-- (0) - Disable both tag removal and tag insertion 
-- 
-- (1) - When packets are output on the port, the switch will remove 
--       802.1q tags from packets with 802.1q tags when received. 
--       The switch will not add tags to packets already tagged. 
--       The tag inserted is the ingress ports's "port VID." 
--       and
--       Disable tag insertion.
-- 
-- (2) - Disable tag removal 
--       and
--       When packets are output on the port, the switch will add 
--       802.1q tags to packets without 802.1q tags when received. 
--       The switch will not add tags to packets already tagged. 
--       The tag inserted is the ingress port's "port VID".
-- 
-- (3) - When packets are output on the port, the switch will remove 
--       802.1q tags from packets with 802.1q tags when received. 
--       The switch will not add tags to packets already tagged. 
--       The tag inserted is the ingress ports's "port VID." 
--       and
--       When packets are output on the port, the switch will add 
--       802.1q tags to packets without 802.1q tags when received. 
--       The switch will not add tags to packets already tagged. 
--       The tag inserted is the ingress port's "port VID".
		-- 1.3.6.1.4.1.11606.2.25.45.16
		port2CtrlTagInsertionRemoval OBJECT-TYPE
			SYNTAX INTEGER (0..3)
			ACCESS read-write
			STATUS mandatory
			DESCRIPTION
				"Port2 Tag Insertion/Tag Removal"
			::= { port2Ctrl 16 }

		
-- Port based VLAN:
-- Define the port's "Port VLAN membership." Bit 4 stands 
-- for port 5, bit 3 for port 4...bit 0 for port1. The port
-- can only communicate within the membership. A '1' includes 
-- a port in the membership, a '0' excludes a port from membership.
		-- 1.3.6.1.4.1.11606.2.25.45.17
		port2CtrlPortMembership OBJECT-TYPE
			SYNTAX INTEGER (0..31)
			ACCESS read-write
			STATUS mandatory
			DESCRIPTION
				"Port2 Port Membership"
			::= { port2Ctrl 17 }

		
-- Ingress VLAN filtering:
-- (0) - No ingress VLAN filtering.
-- (1) - The switch will discard packets whose VID port membership 
--       in VLAN table bit
		-- 1.3.6.1.4.1.11606.2.25.45.18
		port2CtrlIngressVLANFiltering OBJECT-TYPE
			SYNTAX INTEGER (0..1)
			ACCESS read-write
			STATUS mandatory
			DESCRIPTION
				"Port2 Ingress VLAN Filtering"
			::= { port2Ctrl 18 }

		
-- Discard Non-PVID packet:
-- (0) - No packets will be discarded.
-- (1) - The switch will discard packets whose VID does not 
--       match ingress port default VID.
		-- 1.3.6.1.4.1.11606.2.25.45.19
		port2CtrlDiscardNon-PVIDPkt OBJECT-TYPE
			SYNTAX INTEGER (0..1)
			ACCESS read-write
			STATUS mandatory
			DESCRIPTION
				"Port2 Discard Non-PVID Packet"
			::= { port2Ctrl 19 }

		
-- Default Tag:
-- This is a 16bit data for Port's default tag, containging:
-- Bit        Description:
-- =======================
-- 0..11   -  VID
-- 12      -  CFG bit
-- 13..15  -  User priority bits
		-- 1.3.6.1.4.1.11606.2.25.45.20
		port2CtrlDefaultTag OBJECT-TYPE
			SYNTAX INTEGER (0..65536)
			ACCESS read-write
			STATUS mandatory
			DESCRIPTION
				"Port2 Default Tag"
			::= { port2Ctrl 20 }

		
-- Forced speed:
-- (0) - Forced 10BT if Auto-Negotiation is disabled
-- (1) - Forced 100BT if Auto-Negotiation is disabled
		-- 1.3.6.1.4.1.11606.2.25.45.21
		port2CtrlForceSpeed OBJECT-TYPE
			SYNTAX INTEGER (0..1)
			ACCESS read-write
			STATUS mandatory
			DESCRIPTION
				"Port2 Force Speed"
			::= { port2Ctrl 21 }

		
-- CPON-100 Uplink (Optical) port
		-- 1.3.6.1.4.1.11606.2.26
		cpon100PriUplink OBJECT IDENTIFIER ::= { cpon100 26 }

		
-- Primary uplink Link status
-- (0) - Link failed
-- (1) - Link good
		-- 1.3.6.1.4.1.11606.2.26.1
		priUplinkLinkStatus OBJECT-TYPE
			SYNTAX INTEGER (0..1)
			ACCESS read-only
			STATUS mandatory
			DESCRIPTION
				"Uplink Link Status"
			::= { cpon100PriUplink 1 }

		
		-- 1.3.6.1.4.1.11606.2.26.45
		priUplinkPortCtrl OBJECT IDENTIFIER ::= { cpon100PriUplink 45 }
-- CPON-100 Uplink Port Controls
		
-- Primary uplink Link Remote loopback test
-- (0) - Normal operation
-- (1) - Perform loopback test
		-- 1.3.6.1.4.1.11606.2.26.45.15
		priUplinkLinkRemoteLoopbackTest OBJECT-TYPE
			SYNTAX INTEGER (0..1)
			ACCESS read-only
			STATUS mandatory
			DESCRIPTION
				"Primary uplink Link Remote loopback test"
			::= { priUplinkPortCtrl 15 }

		
-- Transmit low priority rate control:
-- ===================================
-- A 12-bit field to determine how many "32Kbps" low priority blocks 
-- can be transmitted (in a unit of 4K bytes in a one second period)
-- 
		-- 1.3.6.1.4.1.11606.2.26.45.22
		priUplinkTxLoPriorityRateCtrl OBJECT-TYPE
			SYNTAX INTEGER (0..4095)
			ACCESS read-write
			STATUS mandatory
			DESCRIPTION
				"Primary Uplink Transmit Low Priority Rate Control"
			::= { priUplinkPortCtrl 22 }

		
-- Receive low priority rate control:
-- ===================================
-- A 12-bit field to determine how many "32Kbps" low priority blocks 
-- can be received (in a unit of 4K bytes in a one second period)
-- 
		-- 1.3.6.1.4.1.11606.2.26.45.23
		priUplinkRxLoPriorityRateCtrl OBJECT-TYPE
			SYNTAX INTEGER (0..4095)
			ACCESS read-write
			STATUS mandatory
			DESCRIPTION
				"Primary Uplink Receive Low Priority Rate Control"
			::= { priUplinkPortCtrl 23 }

		
-- Primary uplink port Transmit Differential Priority Rate Control
-- (0) - Will do transmit rate control on any packets. The rate 
--       counters defined in low priority will be used.
-- (1) - Will do transmit rate control on both high and low priority 
--       packets based on the rate counters defined by the high and 
--       low priority packets respectively.
		-- 1.3.6.1.4.1.11606.2.26.45.24
		priUplinkTxDiffPriorityRateCtrl OBJECT-TYPE
			SYNTAX INTEGER (0..1)
			ACCESS read-write
			STATUS mandatory
			DESCRIPTION
				"Primary Uplink Transmit Differential Priority Rate Control"
			::= { priUplinkPortCtrl 24 }

		
-- NOT RELEASE
		-- 1.3.6.1.4.1.11606.3
		odnrt100 OBJECT IDENTIFIER ::= { pbn 3 }

		
-- OSLAM-8G: Optical Subscriber Line Access Multiplexer
-- ====================================================
-- The new and advanced OSLAM-8G fibre optic access multiplexer provides 
-- the basic building block for highly scalable fibre-to-the-home (FTTH) 
-- and fibre-to-the-block (FTTB) applications. With 80 available line ports
-- per OCMR chassis the network costs involved are greatly reduced.
		-- 1.3.6.1.4.1.11606.4
		oslam8g OBJECT IDENTIFIER ::= { pbn 4 }

		
-- OSLAM-8G Global Controls and Status
		-- 1.3.6.1.4.1.11606.4.1
		oslam8g-Global OBJECT IDENTIFIER ::= { oslam8g 1 }

		
-- OSLAM-8G Global Control
		-- 1.3.6.1.4.1.11606.4.1.1
		oslam8g-globalCtrl OBJECT IDENTIFIER ::= { oslam8g-Global 1 }

		
		-- 1.3.6.1.4.1.11606.4.1.1.1
		oslam8gSrcMACAddr OBJECT-TYPE
			SYNTAX Opaque (SIZE (6))
			ACCESS read-write
			STATUS mandatory
			DESCRIPTION
				"OSLAM-8G Source MAC address
				===========================
				48bit Source address MAC address for pause control frame.
				
				NOTE: First bit of 2nd octet is as followed:
				
				This bit used to have all ports transmit the same or different
				source addresses in full-duplex Pause frames.
				
				0 - All ports transmit the same Static Address (SA)
				1 - Each port uses a different SA where bits 4:47 of 
				    the 'sourceMACAddress' are the same, but bits 3:0 are the
				    port number (Port 0 = 0, Port1 = 1, Port 2 = 2, etc.)"
			::= { oslam8g-globalCtrl 1 }

		
		-- 1.3.6.1.4.1.11606.4.1.1.2
		oslam8gSchedulingMode OBJECT-TYPE
			SYNTAX INTEGER
				{
				useFairQueuingScheme(1),
				useStrictPriorityScheme(2)
				}
			ACCESS read-write
			STATUS mandatory
			DESCRIPTION
				"OSLAM-8G Scheduling Mode
				=========================
				1 - Use an 8,4,2,1 weighted fair queuing scheme
				2 - Us a strict priority scheme"
			::= { oslam8g-globalCtrl 2 }

		
		-- 1.3.6.1.4.1.11606.4.1.1.3
		oslam8gMaxFrameSize OBJECT-TYPE
			SYNTAX INTEGER
				{
				sizeMax1522Octets(1),
				sizeMax1632Octets(2)
				}
			ACCESS read-write
			STATUS mandatory
			DESCRIPTION
				"Maximum Frame Size allowed.
				===========================
				The Ingress block discards all frames less than 64 bytes in size.
				It also discards all frames greater than a certain size 
				(regardless of whether or not the frame is iEEE802.3ac tagged)
				as follows:
				
				1 - Max size is 1522 for IEEE tagged frames, 1518 for untagged frames.
				2 - Max size is 1632"
			::= { oslam8g-globalCtrl 3 }

		
-- 
-- 
		-- 1.3.6.1.4.1.11606.4.1.1.4
		oslam8gCoreTag OBJECT-TYPE
			SYNTAX INTEGER (0..65535)
			ACCESS read-write
			STATUS mandatory
			DESCRIPTION
				"OSLAM-8G Core Tag Type
				======================
				Core Tag Ether Type. This EtherType is added to frames that egress the
				switch as Double Tagged frames. It is also the EtherType expected during
				Ingress to determine if a frame is Tagged or not on ports configured in
				oslam8gPortEgressMode as follows:
				
				For Ingress:
				===========
				oslam8gUseCoreTag= 1, oslam8gDoubleTag = 1, TagType = 0x8100
				oslam8gUseCoreTag= 1, oslam8gDoubleTag = 2, TagType = 0x8100
				oslam8gUseCoreTag= 2, oslam8gDoubleTag = 1, TagType = oslam8gCoreTagType
				oslam8gUseCoreTag= 2, oslam8gDoubleTag = 2, 1st TagType = oslam8gCoreTagType then 
				                                2nd TagType in the frame = 0x8100
				
				
				For Egress:
				===========
				Normal Add a Tag (standard IEEE rule) Added Tag Type = 0x8100
				Always Add a Tag (Egress DoubleTag)   Added Tag Type = oslam8gCoreTagType"
			::= { oslam8g-globalCtrl 4 }

		
-- 
-- 
		-- 1.3.6.1.4.1.11606.4.1.1.5
		oslam8gUseDoubleTagData OBJECT-TYPE
			SYNTAX INTEGER
				{
				ignoreRemovedTagData(1),
				useRemovedTagData(2)
				}
			ACCESS read-write
			STATUS mandatory
			DESCRIPTION
				"OSLAM-8G Use Double Tag Data
				============================
				Used to determine if Double Tag data is removed from a Double Tag 
				frame is used or ignored when making switching decisions on the frame.
				
				1 - Ignore removed Tag data
				2 - Use removed Tag data
				
				This OID have not effect if hte port's oslam8gPortDoubleTag is set to 1"
			::= { oslam8g-globalCtrl 5 }

		
-- OSLAM-8G Global Status
		-- 1.3.6.1.4.1.11606.4.1.2
		oslam8g-globalStatus OBJECT IDENTIFIER ::= { oslam8g-Global 2 }

		
		-- 1.3.6.1.4.1.11606.4.1.2.1
		oslam8gSerialNumber OBJECT-TYPE
			SYNTAX DisplayString
			ACCESS read-only
			STATUS mandatory
			DESCRIPTION
				"OSLAM-8G Serial Number"
			::= { oslam8g-globalStatus 1 }

		
		-- 1.3.6.1.4.1.11606.4.1.2.2
		oslam8gMACAddress OBJECT-TYPE
			SYNTAX OCTET STRING (SIZE (12))
			ACCESS read-only
			STATUS mandatory
			DESCRIPTION
				"OSLAM-8G SNMP MAC Address"
			::= { oslam8g-globalStatus 2 }

		
		-- 1.3.6.1.4.1.11606.4.1.2.3
		oslam8gDiagnosticMsg OBJECT-TYPE
			SYNTAX DisplayString (SIZE (0..63))
			ACCESS read-only
			STATUS mandatory
			DESCRIPTION
				"OSLAM-8G Diagnostic Message"
			::= { oslam8g-globalStatus 3 }

		
-- 802.1Q VLAN Table
		-- 1.3.6.1.4.1.11606.4.1.3
		oslam8g-VTU OBJECT IDENTIFIER ::= { oslam8g-Global 3 }

		
		-- 1.3.6.1.4.1.11606.4.1.3.1
		vtuOperation OBJECT-TYPE
			SYNTAX INTEGER
				{
				flushAllEntries(1),
				noOperation(2),
				loadOrPurgeEntry(3),
				getNext(4),
				getClearViolation(7)
				}
			ACCESS read-write
			STATUS mandatory
			DESCRIPTION
				"VLAN Table Unit Table Operation
				===============================
				Support the following VTU operation.
				0, 2 - No Operation
				1    - Flush All Entries
				3    - Load(1) or Purge(2) an Entry
				4    - Get Next(3)
				5,6  - Reserve
				7    - Get/Clear Violation Data
				
				NOTE:
				(1) - An Entry is Loaded when the 'vtuValid' is set to a one. 
				      Load is the only 'vtuOperation' that uses the 'vtuDBNum' field 
				      and it uses it as data to be loaded along with the desired 'vtuVID'.
				(2) - An Entry is Purged when the 'vtuValid' is cleared to a zero.
				(3) - A Get Next operation finds the next higher 'vtuVID' curretnly in 
				      the database. The vtuVID value is used as the VID to start from.
				      To find the lowest VID set the vtuVID field to ones. 
				      When the operation is done the vtuVID field contains the next 
				      higher VID currently active in the database. To find the next
				      VID simply issue the Get Next opcode again. If the vtuVID field
				      is returned set to a one's with the vtuValid cleared to zero, 
				      no higher VID's were found. To Search for a particular VID, 
				      perform a Get Next operation using a vtuVID field with a value 
				      one less than the one being searched for."
			::= { oslam8g-VTU 1 }

		
		-- 1.3.6.1.4.1.11606.4.1.3.2
		vtuDBNum OBJECT-TYPE
			SYNTAX INTEGER (0..255)
			ACCESS read-write
			STATUS mandatory
			DESCRIPTION
				"VTU MAC Address Database Number
				===============================
				On all vtuOperation except for Get Violation Data, this field is used to 
				separate MAC address dtabases by a frame's VID. If multiple address databases
				are not being used, theses bits must remain zero. If multiple addresss are not
				being used, theses bits must remain zero. If multiple address databases are 
				being used, these bits are used to get the desired database number that is 
				associated with VID value on Load operations (or used to read the currently
				assigned vtuDBNum on Get Next operations)."
			::= { oslam8g-VTU 2 }

		
		-- 1.3.6.1.4.1.11606.4.1.3.3
		vtuMemberViolation OBJECT-TYPE
			SYNTAX INTEGER
				{
				noViolation(1),
				violation(2)
				}
			ACCESS read-only
			STATUS mandatory
			DESCRIPTION
				"VTU Member Violation
				==================
				Source Member Violation. On Get/Clear Violation Data vtuOperation,
				this value is returned set to a two(2) if the Violation being serviced 
				is due to an 802.1Q Member Violation. A member Violation occurs 
				when an 802.1Q enabled ingress port accesses the VTU with a VID 
				that is cotnained in the VTU but whose Mebership list does not 
				include this Ingress port. 
				Only the first vtuFullViolation, vtuMemberViolation, vtuMissViolation 
				is saved per port until cleared."
			::= { oslam8g-VTU 3 }

		
		-- 1.3.6.1.4.1.11606.4.1.3.4
		vtuMissViolation OBJECT-TYPE
			SYNTAX INTEGER
				{
				noViolation(1),
				violation(2)
				}
			ACCESS read-only
			STATUS mandatory
			DESCRIPTION
				"VTU Miss Violation
				==================
				On Get/Clear Violation operation this value is set to a two(2) if the 
				Violation being serviced is due to 802.1Q Miss Violation. A Miss 
				Violation occurs when an 802.1Q enabled Ingress port accesses the
				VTU with a VID that is contained in the VTU.
				
				Only the first atuFullViolation, atuMemberViolation, atuMissViolation 
				is saved per port until cleared."
			::= { oslam8g-VTU 4 }

		
		-- 1.3.6.1.4.1.11606.4.1.3.5
		vtuValid OBJECT-TYPE
			SYNTAX INTEGER
				{
				invalidVIDOrEndOflist(1),
				validVID(2)
				}
			ACCESS read-write
			STATUS mandatory
			DESCRIPTION
				"VTU Entry Valid status.
				=======================
				At the end of Get/Next operations
				1 - If VID is all ones, it indicates the end of the VID list was reached
				    with no new valid entries.
				2 - Indicates the VID value below is valid.
				
				NOTE: On Load or Purge operations, this bit indicates the desired operation 
				      of a Load (when set to a one) or a Purge (when cleared to a zero)."
			::= { oslam8g-VTU 5 }

		
-- 
-- 
		-- 1.3.6.1.4.1.11606.4.1.3.6
		vtuVID OBJECT-TYPE
			SYNTAX INTEGER (0..4095)
			ACCESS read-write
			STATUS mandatory
			DESCRIPTION
				"VLAN Identifier
				===============
				This VID is used in all the vtuOperation commands (except Get/Clear
				Violation Data) and it is the VID that is associated with the vtuData
				or the vtuVID that caused the VTU Violation.
				
				Theses indicate the VID number that is associated with the MemberTag
				in the vtuData, 802.1s PortState, Priority and its override."
			::= { oslam8g-VTU 6 }

		
		-- 1.3.6.1.4.1.11606.4.1.3.7
		vtuData OBJECT-TYPE
			SYNTAX Opaque (SIZE (6))
			ACCESS read-write
			STATUS mandatory
			DESCRIPTION
				"VLAN table data
				Entry Format as follow:
				======================
				
				BYTE#:      5      4      3      2      1      0
				Frame:   [0:P10][P9:P8][P7:P6][P5:P4][P3:P2][P1:P0]
				
				Px:       Port control
				          Size: 4bits total
				          Format: [PortState][PortMemberTag]
				
				          PortState: The upper two bits of each port's VTU data is called 802.1s PortState.
				                     These bits are used to support 802.1s per VLAN spanning tree as follows:
				                     00 - 802.1s Disabled. User non-VLAN Port states (in Port control 'portState')
				                     01 - Blocking/Listening Port State for this port for frames with this VID
				                     10 - Learning Port State for this port for frames with this VID
				                     11 - Forwarding Port State for this port for frames with this VID
				               NOTE: These 802.1s PortState bits take precedence over the port's 'portState'
				                     in port control unless the port's 'portState' is Disabled 
				                     (which prevents all frames from flowing).
				          MemberTag: Size: 2bits
				                     The lower two bits of each port's VTU data is called MemberTag.
				                     These bits are used to indicate which ports are members of
				                     the VLAN and if these VLANs frames should be tagged or
				                     untagged, or unmodified when exiting the port as follows:
				                     00 - Port is a member of this VLAN and frames are to egress unmodified.
				                     01 - Port is a member of this VLAN and frames are to egress Untagged.
				                     10 - Port is a member of this VLAN and frames are to egress Tagged.
				                     11 - Port is not a member of this VLAN"
			::= { oslam8g-VTU 7 }

		
		-- 1.3.6.1.4.1.11606.4.1.3.8
		vtuVIDPRI OBJECT-TYPE
			SYNTAX INTEGER (0..7)
			ACCESS read-write
			STATUS mandatory
			DESCRIPTION
				"VID Priority
				============
				These bits are used to override the priority on any frames associated with this
				VID value, if the 'vtuVIDPRIOverride' is set to one."
			::= { oslam8g-VTU 8 }

		
		-- 1.3.6.1.4.1.11606.4.1.3.9
		vtuVIDPRIOverride OBJECT-TYPE
			SYNTAX INTEGER
				{
				noPriorityOverride(1),
				priorityOverride(2)
				}
			ACCESS read-write
			STATUS mandatory
			DESCRIPTION
				"VID Priority Override
				=====================
				1 - No priority override.
				2 - The vtuVIDPRI are used to override the priority on any frames associated 
				    with this VID as long as the port's 'portVTUPriOverride' is set.
				"
			::= { oslam8g-VTU 9 }

		
		-- 1.3.6.1.4.1.11606.4.1.4
		oslam8g-ATU OBJECT IDENTIFIER ::= { oslam8g-Global 4 }

		
		-- 1.3.6.1.4.1.11606.4.1.4.1
		atuOperation OBJECT-TYPE
			SYNTAX INTEGER
				{
				flushAllEntries(1),
				flushAllDynamicEntries(2),
				loadOrPurgeEntry(3),
				getNext(4),
				flushAllStaticIntriesInSelectedDBNum(5),
				flushAllDynamicEntriesInSelectedDBNum(6),
				getClearViolation(7),
				noOperation(8)
				}
			ACCESS read-write
			STATUS mandatory
			DESCRIPTION
				"Address Translation Unit (ATU) Opcode:
				======================================
				1 - Flush All Entries
				2 - Flush all Non-Static Entries
				3 - Load or Purge an Entry in a particular atuDBNum Database
				4 - Get Next from a particular atuDBNum Database
				5 - Flush all Entries in a particular atuDBNum Database
				6 - Flush all Non-Static Entries in a particular atuDBNum Database
				7 - Get/Clear Violation Data.
				8 - No operation"
			::= { oslam8g-ATU 1 }

		
		-- 1.3.6.1.4.1.11606.4.1.4.2
		atuDBNum OBJECT-TYPE
			SYNTAX INTEGER (0..255)
			ACCESS read-write
			STATUS mandatory
			DESCRIPTION
				"ATU MAC Address Database Number (DBNum)
				=======================================
				If multiple address databases are not being used theses bits must remain zero.
				If multiple address databases are being used theses are used to set the desired
				address database number that is being used on the Database supported commands
				(atuOperation 0x03, 0x04, 0x05 and 0x06). On Get/Clear Violation Data 
				atuOperation these bits return the atuDBNum value associated with the ATU
				violation that was just serviced."
			::= { oslam8g-ATU 2 }

		
		-- 1.3.6.1.4.1.11606.4.1.4.3
		atuMemberViolation OBJECT-TYPE
			SYNTAX INTEGER
				{
				noViolation(1),
				violation(2)
				}
			ACCESS read-only
			STATUS mandatory
			DESCRIPTION
				"ATU Member Violation
				==================
				On Get/Clear Violation operation this value is set to a two(2) if the 
				Violation being serviced is due to a Source Address Look-up that 
				resulted in a Hit but where the 'atuState' and 'atuPortVec' bits 
				does not contain the frame's Ingress port bit set to a two(2)
				(i.e. a station moved occurred). This violation can be masked on
				a per port basis by setting the port's ignoreWrongData bit. Only
				the first atuFullViolation, atuMemberViolation, atuMissViolation 
				is saved per port until cleared."
			::= { oslam8g-ATU 3 }

		
		-- 1.3.6.1.4.1.11606.4.1.4.4
		atuMissViolation OBJECT-TYPE
			SYNTAX INTEGER
				{
				noViolation(1),
				violation(2)
				}
			ACCESS read-only
			STATUS mandatory
			DESCRIPTION
				"ATU Miss Violation
				==================
				On Get/CLear Violation operation this value is set to a two(2) if the 
				Violation being serviced is due to a Source Address Look-up that 
				resulted in a Miss on ports that are locked (i.e., CPU directed 
				learning is enabled on the port). 
				
				Only the first atuFullViolation,
				atuMemberViolation, atuMissViolation is saved per port until cleared."
			::= { oslam8g-ATU 4 }

		
		-- 1.3.6.1.4.1.11606.4.1.4.5
		atuFullViolation OBJECT-TYPE
			SYNTAX INTEGER
				{
				noViolation(1),
				violation(2)
				}
			ACCESS read-only
			STATUS mandatory
			DESCRIPTION
				"ATU Full Violation
				==================
				On Get/Clear Violation operation this value is set to a two(2) if the 
				Violation being serviced is due to a Load operation or automatic 
				learn that could not store the desired entry. This only occurs if
				all available locations for the desired address contain other MAC
				addresses that are loaded Static. Only the first atuFullViolation,
				atuMemberViolation, atuMissViolation is saved per port until cleared."
			::= { oslam8g-ATU 5 }

		
		-- 1.3.6.1.4.1.11606.4.1.4.6
		atuAgeTime OBJECT-TYPE
			SYNTAX INTEGER (0..255)
			ACCESS read-write
			STATUS mandatory
			DESCRIPTION
				"ATU Age Time
				============
				These bits determine the time that each ATU Entry remains valid in the database,
				since its last access as a source address, before being purged. The value in 
				this register times 15 is the age time in seconds. For example: The default value
				of 0x14 is 20 decimal. 20x15 = 300 seconds or 5 minutes. If the atuAgeTime is 0xFF
				or 3825 seconds or almost 64 minutes. if the atuAgeTime is set to 0 the Aging
				function is disabled and all learned addresses will remain in the database forever."
			::= { oslam8g-ATU 6 }

		
		-- 1.3.6.1.4.1.11606.4.1.4.7
		atuTrunkMode OBJECT-TYPE
			SYNTAX INTEGER
				{
				portVectorMode(1),
				trunkIDMode(2)
				}
			ACCESS read-only
			STATUS mandatory
			DESCRIPTION
				"TRUNK - Trunk Mappped Address
				=============================
				1 - The 'atuPortVec'  is the port vector assigned to this address.
				
				2 - The data bits [7:4] of 'atuPortVec' 
				is the Trunk ID assigned to this address. 'atuPortVec' bits [10:4]
				must be written as zero when this value is zet to a two(2).
				
				"
			::= { oslam8g-ATU 7 }

		
		-- 1.3.6.1.4.1.11606.4.1.4.8
		atuPortVecorTrunkID OBJECT-TYPE
			SYNTAX INTEGER (0..255)
			ACCESS read-write
			STATUS mandatory
			DESCRIPTION
				"Port Vector/Trunk ID
				====================
				If the atuTrunk is zero, theses bits are used as the input Port Vector 
				for ATU Load operations and it's the resulting Trunk ID for ATU load 
				operations and it's the resulting Trunk ID from ATU GetNext operations."
			::= { oslam8g-ATU 8 }

		
		-- 1.3.6.1.4.1.11606.4.1.4.9
		atuEntryState OBJECT-TYPE
			SYNTAX INTEGER (0..15)
			ACCESS read-write
			STATUS mandatory
			DESCRIPTION
				"ATU Entry State
				===============
				Used as the Entry State for ATU Load/Purge or Flush/Move
				operations and it is the resulting Entry State from ATU Get Next operations
				(GetNext is the only ATU operation supported in the devices). If theses equal
				to 0x0 then the atuOperation is a Purge or a Flush. If theses bits are not 
				0x0 then the atuOperation is a Load or a Move (a move atuOperation requires
				these bits to be 0x0F). On Get/Clear Violation Data atuOperation, 
				theses bits return the Source Port ID(SPID) associated with the ATU 
				violation that was just serviced. If SPID = 0xF the source of the violation was
				the CPU's register interface (i.e. the ATU was full during a CPU Load operation)."
			::= { oslam8g-ATU 9 }

		
		-- 1.3.6.1.4.1.11606.4.1.4.10
		atuMACEntry OBJECT-TYPE
			SYNTAX Opaque (SIZE (6))
			ACCESS read-write
			STATUS mandatory
			DESCRIPTION
				"ATU MAC Address Entry:
				======================
				Byte pattern as follow:
				
				Opaque data Location:  5  4  3  2  1  0
				MAC Byte Location   : [5][4][3][2][1][0]"
			::= { oslam8g-ATU 10 }

		
-- OSLAM-8G Port Specific Status and Control
		-- 1.3.6.1.4.1.11606.4.2
		oslam8g-Port OBJECT IDENTIFIER ::= { oslam8g 2 }

		
		-- 1.3.6.1.4.1.11606.4.2.1
		oslam8gPortSelect OBJECT-TYPE
			SYNTAX INTEGER
			ACCESS read-write
			STATUS mandatory
			::= { oslam8g-Port 1 }

		
-- OSLAM-8G Port Control
		-- 1.3.6.1.4.1.11606.4.2.2
		oslam8g-portCtrl OBJECT IDENTIFIER ::= { oslam8g-Port 2 }

		
		-- 1.3.6.1.4.1.11606.4.2.2.1
		oslam8gPortForceFlowCtrl OBJECT-TYPE
			SYNTAX INTEGER
				{
				forceNoFlowCtrl(1),
				normal(2),
				forceFlowCtrl(3)
				}
			ACCESS read-write
			STATUS mandatory
			DESCRIPTION
				"OSLAM-8G Port Force Flow Control Setting
				========================================
				1 - Force No Flow Control
				2 - Normal detection occurs
				3 - Force Flow Control"
			::= { oslam8g-portCtrl 1 }

		
		-- 1.3.6.1.4.1.11606.4.2.2.2
		oslam8gPortForceLink OBJECT-TYPE
			SYNTAX INTEGER
				{
				forceLinkDown(1),
				normal(2),
				forceLinkUp(3)
				}
			ACCESS read-write
			STATUS mandatory
			DESCRIPTION
				"OSLAM-8G Port Force Link
				========================
				1 - Force to bring link down
				2 - Normal link detection occurs
				3 - Force to bring link up"
			::= { oslam8g-portCtrl 2 }

		
		-- 1.3.6.1.4.1.11606.4.2.2.3
		oslam8gPortForceDuplex OBJECT-TYPE
			SYNTAX INTEGER
				{
				forceHalfDuplex(1),
				normal(2),
				forceFullDuplexx(3)
				}
			ACCESS read-write
			STATUS mandatory
			DESCRIPTION
				"OSLAM-8G Port Force Duplex Control
				==================================
				1 - Force Half-Duplex
				2 - Normal duplex detection occurs.
				3 - Force Full-Duplex"
			::= { oslam8g-portCtrl 3 }

		
		-- 1.3.6.1.4.1.11606.4.2.2.4
		oslam8gPortForceSpeed OBJECT-TYPE
			SYNTAX INTEGER
				{
				speed10Mbps(1),
				speed100Mbps(2),
				speed1000Mbps(3),
				speedAutoDetect(4)
				}
			ACCESS read-write
			STATUS mandatory
			DESCRIPTION
				"OSLAM-8G Port Force Speed
				=========================
				1 - 10Mbps
				2 - 100Mbps
				3 - 1000Mbps
				4 - Speed is not forced. Normal speed detection occurs."
			::= { oslam8g-portCtrl 4 }

		
		-- 1.3.6.1.4.1.11606.4.2.2.5
		oslam8gPortPortState OBJECT-TYPE
			SYNTAX INTEGER
				{
				disabled(1),
				blockingListening(2),
				learning(3),
				forwarding(4)
				}
			ACCESS read-write
			STATUS mandatory
			DESCRIPTION
				"OSLAM-8G Port's Port State
				===========================
				This OID is used to manage a port to determine what kind of frames, 
				if any, are allowed to enter or leave a port for simple bridge loop
				detection or 802.1D Spanning Tree. This OID value can be change at 
				any time without disrupting frames currently in transmit.
				
				1 - Disabled. 
				    The port is disabled and it will not receive or transmit any frames.
				    The QC returns any pre-allocated ingress queue buffers when the 
				    port is in this mode.
				2 - Blocking/Listening. 
				    OSLAM-8G examines all frames without learning any SAs, and discards
				    all frames.
				3 - Learning.
				    OSLAM-8G will examine all frames, learning all SA address (except those
				    from MGMT frames), and still discard all but MGMT frames. It will allow
				    MGMT frames only to exit the port.
				4 - Forwarding.
				    OSLAM-8G examines all frames, learning SAs from all good frames (except 
				    those from MGMT frames), and receives and transmits all frames as a normal switch."
			::= { oslam8g-portCtrl 5 }

		
		-- 1.3.6.1.4.1.11606.4.2.2.6
		oslam8gPortFwdUnknown OBJECT-TYPE
			SYNTAX INTEGER
				{
				blockUnicastWithUnknownDA(1),
				normalForward(2)
				}
			ACCESS read-write
			STATUS mandatory
			DESCRIPTION
				"OSLAM-8G Port Forward Unknown
				=============================
				1 - Unicast frames with unknown DAs will not egress out of this port.
				2 - Normal operation occurs and unicast frames with unknown DA addresses 
				    are allowed to egress out of this port (assuming the VLAN settings 
				    allow the frame to egress this port too)."
			::= { oslam8g-portCtrl 6 }

		
		-- 1.3.6.1.4.1.11606.4.2.2.7
		oslam8gPortDefFwd OBJECT-TYPE
			SYNTAX INTEGER
				{
				blockMulticastWithUnknownDA(1),
				normalForward(2)
				}
			ACCESS read-write
			STATUS mandatory
			DESCRIPTION
				"OSLAM-8G Port Default Forward
				=============================
				1 - Multicast frames with unknown DAs do not egress from this port.
				2 - Normal switch operation occurs and multicast frames with unknown
				    DA addresses are allowed to egress out this port (assuming the
				    VLAN settings allow the frame to egress this port too)."
			::= { oslam8g-portCtrl 7 }

		
		-- 1.3.6.1.4.1.11606.4.2.2.8
		oslam8gPortUseIPForPriority OBJECT-TYPE
			SYNTAX INTEGER
				{
				useIPv4AndIPv6Priority(1),
				useIPv4OrIPv6Priority(2)
				}
			ACCESS read-write
			STATUS mandatory
			DESCRIPTION
				"OSLAM-8G Port Use IP for Priority
				=================================
				Use IPv4 TOS and/or DiffServ fields and/or IPv6 Traffic Class fields, 
				if present, for priority data.
				
				1 - Ignore IPv4 and IPv6 priority fields.
				2 - Use IPv4 fields if the frame is IPv4 and use IPv6 fields 
				    if the frame is IPv6 for priority data.
				"
			::= { oslam8g-portCtrl 8 }

		
		-- 1.3.6.1.4.1.11606.4.2.2.9
		oslam8gPortUseCoreTag OBJECT-TYPE
			SYNTAX INTEGER
				{
				normal(1),
				useCoreTag(2)
				}
			ACCESS read-write
			STATUS mandatory
			DESCRIPTION
				"OSLAM-8G Port Use Core Tag
				==========================
				Refer to 'oslam8gCoreTag'
				
				1 - Ingressing frames are considered tagged if the 16-bits 
				    following the frame's source Address are 0x8100.
				2 - Ingressing frames are considered tagged if the 16-bits
				    following the frame's source Address are equal to
				    'oslam8gCoreTagType'
				
				NOTE: 
				   If a frame is Double Tagged and the first tag is removed 
				   (oslam8gPortDoubleTag) by matching the EtherType define by
				   this bit, the resulting frame will be considered tagged 
				   only if the next 16 bits in the frame equal to 0x8100 
				   (that is, the oslam8gCoreTagType is not used after the
				   first tag is removed)"
			::= { oslam8g-portCtrl 9 }

		
		-- 1.3.6.1.4.1.11606.4.2.2.10
		oslam8gPortDoubleTag OBJECT-TYPE
			SYNTAX INTEGER
				{
				normal(1),
				useDoubleCoreTag(2)
				}
			ACCESS read-write
			STATUS mandatory
			DESCRIPTION
				"OSLAM-8G Port Double Tag
				========================
				Ingress Double Tag
				
				2 - The ingressing frames are examined to see if they contain 802.3ac 
				    tag with the IEEE standard EtherType of 0x8100 or if they contain
				    a tag with an EtherType defined in oslam8gCoreTag. The oslam8gCoreTag
				    will be used if this port's oslam8gPortUseCoreTag is used. If the 
				    frames do contain the expected tag, the tag is removed (and the 
				    CRC is recomputed).
				
				    Essentially, untagged frames remain untagged, single tagged frames
				    become untagged and double tagged frames become single tagged. 
				    These now single tagged frames will be considered tagged only if 
				    its EtherType value is 0x8100 no matter what the EtherType value 
				    was found on the removed tag. No padding is performed so a tagged
				    frame must be at least 68bytes in size or it will be discarded.
				
				1 - Tagged frames are not modified when received.
				
				    The Tag data that is removed from the frame can be ignored 
				    (i.e., the frame is treated as if the removed tag never existed)
				    or the removed Tag data can be used for switching and priority
				    decisions (i.e., the removed Tag's VID and PRI bits are internally 
				    assigned to the frame). The action that is taken is controlled by
				    the oslam8gUseDoubleTagData"
			::= { oslam8g-portCtrl 10 }

		
-- OSLAM-8G Port Rate Control
		-- 1.3.6.1.4.1.11606.4.2.3
		oslam8g-portRateCtrl OBJECT IDENTIFIER ::= { oslam8g-Port 3 }

		
		-- 1.3.6.1.4.1.11606.4.2.3.1
		oslam8gPortEgressRate OBJECT-TYPE
			SYNTAX INTEGER (0..4095)
			ACCESS read-write
			STATUS mandatory
			DESCRIPTION
				"OSLAM-8G Port Egress Rate Limit
				================================
				Modify this port's effective transmission rate. This support 62kbps to 256Mbps.
				
				Formula to limit the Egress data rate:
				
				EgressRate = 8 bits/ (32ns * Egress Rate bits/sec)
				
				Where,
				=> Egress Rate is in bits per second.
				
				For example:
				============
				For 256Kbps rate the value of this oslam8gPortEgressRate should be:
				  = 8/(32ns * 256Kbps) = 976
				The value to be programmed for this OID is 976. 976 is actually equated to 256.14Kbps"
			::= { oslam8g-portRateCtrl 1 }

		
		-- 1.3.6.1.4.1.11606.4.2.3.2
		oslam8gPortIngressLimitMode OBJECT-TYPE
			SYNTAX INTEGER
				{
				limitAllFrames(1),
				limitBroadcastMulticastUnicastFrame(2),
				limitBroadcastMulticastFrame(3),
				limitBroadcastFrame(4)
				}
			ACCESS read-write
			STATUS mandatory
			DESCRIPTION
				"OSLAM-8G Port Ingress Limit Mode
				================================
				Determine what kinds of frames are limited and counted against Ingress limiting.
				1 - Limit and count all frames.
				2 - Limit and count Broadcast, Multicast and flooded unicast frames.
				3 - Limit and count Broadcast and Multicast frames only.
				4 - Limit and count Broadcast frames only.
				
				NOTE: 
				If a frame is not limited by the above setting, its size is not counted against 
				the limit for the other frames."
			::= { oslam8g-portRateCtrl 2 }

		
		-- 1.3.6.1.4.1.11606.4.2.3.3
		oslam8gPortIngressPri3Rate OBJECT-TYPE
			SYNTAX INTEGER
				{
				useIngressPri2Rate(1),
				useTwiceIngressPri2Rate(2)
				}
			ACCESS read-write
			STATUS mandatory
			DESCRIPTION
				"OSLAM-8G Port Priority 3 Rate Control
				=====================================
				Priority 3 frames are discarded after the ingress rate selected 
				below is reached or exceeded:
				1 - Use the same rate as oslam8gPortIngressPri2Rate
				2 - Use twice the rate as oslam8gPortIngressPri2Rate 
				    (but no faster than the port's speed)"
			::= { oslam8g-portRateCtrl 3 }

		
		-- 1.3.6.1.4.1.11606.4.2.3.4
		oslam8gPortIngressPri2Rate OBJECT-TYPE
			SYNTAX INTEGER
				{
				useIngressPri1Rate(1),
				useTwiceIngressPri1Rate(2)
				}
			ACCESS read-write
			STATUS mandatory
			DESCRIPTION
				"OSLAM-8G Port Priority 2 Rate Control
				=====================================
				Priority 2 frames are discarded after the ingress rate selected 
				below is reached or exceeded:
				1 - Use the same rate as oslam8gPortIngressPri1Rate
				2 - Use twice the rate as oslam8gPortIngressPri1Rate 
				    (but no faster than the port's speed)"
			::= { oslam8g-portRateCtrl 4 }

		
		-- 1.3.6.1.4.1.11606.4.2.3.5
		oslam8gPortIngressPri1Rate OBJECT-TYPE
			SYNTAX INTEGER
				{
				useIngressPri0Rate(1),
				useTwiceIngressPri0Rate(2)
				}
			ACCESS read-write
			STATUS mandatory
			DESCRIPTION
				"OSLAM-8G Port Priority 1 Rate Control
				=====================================
				Priority 1 frames are discarded after the ingress rate selected 
				below is reached or exceeded:
				1 - Use the same rate as oslam8gPortIngressPri0Rate
				2 - Use twice the rate as oslam8gPortIngressPri0Rate 
				    (but no faster than the port's speed)"
			::= { oslam8g-portRateCtrl 5 }

		
		-- 1.3.6.1.4.1.11606.4.2.3.6
		oslam8gPortIngressPri0Rate OBJECT-TYPE
			SYNTAX INTEGER (0..4095)
			ACCESS read-write
			STATUS mandatory
			DESCRIPTION
				"OSLAM-8G Port Priority 0 Rate Control
				=====================================
				Priority 1 frames are discarded after the ingress rate selected 
				below is reached or exceeded:
				
				OSLAM-8G use the following formula to calculate rate limiting:
				
				Pri0Rate = 8 bits/ (32ns * Ingress Rate bits/sec)
				
				Where,
				=> Ingress Rate is in bits per second.
				
				For example:
				============
				For 128Kbps rate the value of this oslam8gPortEgressRate should be:
				  = 8/(32ns * 128Kbps)
				  = 1953"
			::= { oslam8g-portRateCtrl 6 }

		
-- OSLAM-8G Port VLAN Specific Setting
		-- 1.3.6.1.4.1.11606.4.2.4
		oslam8g-PortVLAN OBJECT IDENTIFIER ::= { oslam8g-Port 4 }

		
		-- 1.3.6.1.4.1.11606.4.2.4.1
		oslam8gPortUseTag OBJECT-TYPE
			SYNTAX INTEGER
				{
				ignoreIEEE802dot1pTag(1),
				useIEEE802dot1pTag(2)
				}
			ACCESS read-write
			STATUS mandatory
			DESCRIPTION
				"OSLAM-8G Port Use Tag
				=====================
				Use IEEE Tags. Use IEEE 802.1p Traffic Class field for priority data if 
				the frame is an IEEE 802.3ac tagged frame.
				1 - Ignore IEEE 802.1p tag fields even it the frame is tagged. 
				    In this mode, tagged frames that enter this port and egress the 
				    OSLAM-8G tagged are re-tagged with this port's default priority bits, 
				    if no other priorities are determined fro the frame (i.e., the frame's
				    IP priority and/or other priority overrides). This works as a Force 
				    Default Priority function on tagged frames.
				2 - Use IEEE 802.1p tag Traffic Class for priority data if the frame is tagged.
				"
			::= { oslam8g-PortVLAN 1 }

		
		-- 1.3.6.1.4.1.11606.4.2.4.2
		oslam8gPortPortMembership OBJECT-TYPE
			SYNTAX INTEGER (0..2047)
			ACCESS read-write
			STATUS mandatory
			DESCRIPTION
				"OSLAM-8G Port's Port Membership
				===============================
				Port based VLAN Table. The bits in this value are used to restrict 
				which output ports this input port can send frames to. This value 
				are used for all frames even if 802.1Q is enabled on this port or 
				if ProtectedPort is enabled on this port. These bits restrict where
				a port can send frames (unless a oslam8gPortVLANTunnel frame is
				being received.
				
				=> To send frames to Port 0, bit 0 of this register must be a one.
				=> To send frames to Port 1, bit 1 of this register must be a one. etc.
				"
			::= { oslam8g-PortVLAN 2 }

		
		-- 1.3.6.1.4.1.11606.4.2.4.3
		oslam8gPortDefPri OBJECT-TYPE
			SYNTAX INTEGER (0..7)
			ACCESS read-write
			STATUS mandatory
			DESCRIPTION
				"OSLAM-8G Port Default Priority
				==============================
				Used as the default ingress priority to use when no other priority
				information is available (neither is the frame IEEE Tagged, nor is
				it an IPv4 nor an IPv6 frame - or the frame is a priority type that
				is currently disabled (see oslam8gPortUseIPPriority and oslam8gPortUseTag)
				and no other priority overrides are active on this frame. The default
				priority are remapped by the oslam8gPortPriRemap prior being used."
			::= { oslam8g-PortVLAN 3 }

		
		-- 1.3.6.1.4.1.11606.4.2.4.4
		oslam8gPort802dot1QMode OBJECT-TYPE
			SYNTAX INTEGER
				{
				portBasedVLANOnly(1),
				fallback802dot1Q(2),
				check802dot1Q(3),
				secure802dot1Q(4)
				}
			ACCESS read-write
			STATUS mandatory
			DESCRIPTION
				"OSLAM-8G Port 802.1Q Mode
				=========================
				IEEE 802.1Q Mode for this port. These bits determine if 802.1Q based 
				VLANs are used along with port based VLANs for this Ingress port. 
				If also determines the action to be taken if an 802.1Q VLAN Violation
				is detected.
				
				1 - 802.1Q disabled. 
				    Use Port Based VLANs only. The oslam8gPortMembership and 
				    oslam8gPortDefVID assigned to the frame during ingress 
				    determine which Egress ports this Ingress is allowed to
				    switch frames to for all frames.
				2 - Fallback.
				    Enable 802.1Q for this Ingress port. Do not discard Ingress
				    Membership violations and use the oslam8gPortMembership 
				    if the frame's VID is not contained in the VTU.
				3 - Check.
				    Enabled 802.1Q for this Ingress port. Do not discard Ingress
				    Membership violation but discard the frame if its VID is not
				    contained in the VTU.
				4 - Secure.
				    Enabled 802.1Q for this Ingress port. Do not discard Ingress
				    Membership violations and discard frames whose VID is not 
				    contained in the VTU.
				"
			::= { oslam8g-PortVLAN 4 }

		
		-- 1.3.6.1.4.1.11606.4.2.4.5
		oslam8gPortTagUntagDiscard OBJECT-TYPE
			SYNTAX INTEGER
				{
				noDiscard(1),
				discardUnTaggedFrames(2),
				discardTaggedFrames(3),
				discardBoth(4)
				}
			ACCESS read-write
			STATUS mandatory
			DESCRIPTION
				"OSLAM-8G Port Tagged/Untagged Discard Mode
				==========================================
				1 - No discard of Frames
				2 - Only Discard Untagged Frames.
				    All non-MGMT frames that are processed as untagged are discarded 
				    as they entering this switch port. This test is performed after 
				    Ingress Double Tag removal (if enabled).
				3 - Only Discard Tagged Frames.
				    All non-MGMT frames that are processed as tagged are discarded 
				    as they entering this switch port.
				    This test is performed after Ingress Double Tag removal (if enabled).
				    Priority only tagged frames (with a VID of 0x00) are considered tagged.
				4 - Both Discard Tagged and Untagged frames."
			::= { oslam8g-PortVLAN 5 }

		
		-- 1.3.6.1.4.1.11606.4.2.4.6
		oslam8gPortDefVID OBJECT-TYPE
			SYNTAX INTEGER (0..4095)
			ACCESS read-write
			STATUS mandatory
			DESCRIPTION
				"OSLAM-8G Port Default VLAN Identifier
				=====================================
				When 802.1Q is enabled on this port this value is used as the IEEE 
				Tagged VID added to untagged or priority tagged frames during egress
				that ingressed from this port. It is also used as a tagged frame's 
				VID if the frame's VID was 0 (i.e., it is a priority tagged frame) 
				or if the port's oslam8gPortForceDefVID is set to one.
				
				When 802.1Q is disabled on this port, this value field is assigned
				to all frames entering the port (if are tagged or untagged). 
				This assignment is used internal to the switch, so only Port 
				Based VLANs can be supported."
			::= { oslam8g-PortVLAN 6 }

		
		-- 1.3.6.1.4.1.11606.4.2.4.7
		oslam8gPortVLANTunnel OBJECT-TYPE
			SYNTAX INTEGER
				{
				vlanNoTunnelling(1),
				vlanTunnelling(2)
				}
			ACCESS read-write
			STATUS mandatory
			DESCRIPTION
				"OSLAM-8G Port VLAN Tunnel
				=========================
				1 - The port based VLANs defined in oslam8gPortPortMembership, 
				    802.1Q VLANs defined in the oslam8g-802dot1QVLAN (if 802.1Q
				    is enabled) and oslam8gTrunkMask are enforced for ALL frames.
				
				2 - The port based oslam8gPortPortMembership, 802.1Q VLAN membership 
				    masking and oslam8gTrunkMask is bypassed for any frame entering
				    this port with a DA that is currently 'static' in the oslam8g-atu.
				    This applies to unicast as well as multicast frames."
			::= { oslam8g-PortVLAN 7 }

		
		-- 1.3.6.1.4.1.11606.4.2.4.8
		oslam8gPortVTUPriOverride OBJECT-TYPE
			SYNTAX INTEGER
				{
				normalPriority(1),
				vtuPriOverride(2)
				}
			ACCESS read-write
			STATUS mandatory
			DESCRIPTION
				"OSLAM-8G Port VTU Priority Override
				===================================
				1 - Normal frame priority processing occurs.
				2 - The VTU priority overrides can occur on this port. 
				    A VTU priority override occurs when the determined 
				    VID of a frame resuls in a VID whose oslam8gVTUVIDPRIOverride 
				    in the VTU VLAN database is set. When this occurs the VIDPRI 
				    value assigned to the frame's VID is used to overrite the frames
				    previously determined priority. If the frame egresses tagged the
				    priority in the frame will be this new VIDPRI value. When used
				    the upper two bits of the VIDPRI priority determine the Egress
				    Queue the frame is switched into. THE VTU Priority Override has 
				    higher priority than the port's Default Priority and the frame's
				    IEEE and/or IP priorities. The priority determined by the frame's
				    VID can be overridden, however, by the frame's SA and/or DA prority
				    Overrides."
			::= { oslam8g-PortVLAN 8 }

		
		-- 1.3.6.1.4.1.11606.4.2.4.9
		oslam8gPortForceDefVID OBJECT-TYPE
			SYNTAX INTEGER
				{
				vidNormal(1),
				forceDefaultVID(2)
				}
			ACCESS read-write
			STATUS mandatory
			DESCRIPTION
				"OSLAM-8G Port Force Default VID
				===============================
				For to use Default VID. When 802.1Q is enabled on this port and 
				
				1 - All IEEE 802.3ac Tagged frames with a non-zero VID used the frame's 
				    VID unmodified.
				
				2 - All ingress frames with IEEE 802.3ac Tags have their VID 
				    ignored and the port's oslam8gPortDefaultVID is used and replaced into 
				    the frame instead. 
				
				When 802.1Q is disabled on this port, this bit has no effect."
			::= { oslam8g-PortVLAN 9 }

		
		-- 1.3.6.1.4.1.11606.4.2.4.10
		oslam8gEgressMode OBJECT-TYPE
			SYNTAX INTEGER
				{
				egressNormal(1),
				egressUntaggedRemoveTaggedFrame(2),
				egressTagAddToUntaggedFrame(3),
				egressAddAlways(4)
				}
			ACCESS read-write
			STATUS mandatory
			DESCRIPTION
				"OSLAM-8G Port Egress Mode
				=========================
				The first three Egrress Modes are used as the default Egress mode for 
				frames whose VID is not valid in the oslam8g-802dot1QVLAN or if 802.1Q
				is disabled on the port. The fourth Egress Mode is applied to all 
				frames all the time (if selected) even if 802.1Q is enabled on the port.
				
				1 - Default to Normal mode. Frames are transmitted unmodified.
				2 - Default to Transmit all frames Untagged. Remove the tag from 
				    any tagged frame.
				3 - Default to Transmit all frames Tagged. Add a tag to any untagged frame.
				4 - Always add a Tag (or Egress Double Tag). This setting is not a default 
				    setting. It ignores the MemberTag in vtuData of oslam8g-802dot1QVLAN 
				    for this port. The EtherType used for these inserted tags come from 
				    oslam8gCoreTag."
			::= { oslam8g-PortVLAN 10 }

		
		-- 1.3.6.1.4.1.11606.4.2.4.11
		oslam8gPortPriRemap OBJECT-TYPE
			SYNTAX Opaque (SIZE (4))
			ACCESS read-write
			STATUS mandatory
			DESCRIPTION
				"OSLAM-8G Port IEEE Priority Remapping
				====================================
				
				Byte#:            3                    2                    1                    0
				Format: [TagRemap7:TagRemap6][TagRemap5:TagRemap4][TagRemap3:TagRemap2][TagRemap1:TagRemap0]
				
				TagRemap0: Tag Remap 0. 
				           All IEEE tagged frames with a priority of 0 get this value as the frame's 
				           new priority inside the switch. If a tagged frame egresses the switch tagged,
				           this new priority is written to the frame's tag.
				
				TagRemap1: Tag Remap 1. 
				           All IEEE tagged frames with a priority of 1 get this value as the frame's 
				           new priority inside the switch. If a tagged frame egresses the switch tagged,
				           this new priority is written to the frame's tag.
				
				TagRemapX: Tag Remap X. 
				           All IEEE tagged frames with a priority of X get this value as the frame's 
				           new priority inside the switch. If a tagged frame egresses the switch tagged,
				           this new priority is written to the frame's tag."
			::= { oslam8g-PortVLAN 11 }

		
-- OSLAM-8G Port Status
		-- 1.3.6.1.4.1.11606.4.2.5
		oslam8g-portStatus OBJECT IDENTIFIER ::= { oslam8g-Port 5 }

		
		-- 1.3.6.1.4.1.11606.4.2.5.1
		oslam8gPortLinkStatus OBJECT-TYPE
			SYNTAX INTEGER
				{
				linkDown(1),
				linkUp(2)
				}
			ACCESS read-only
			STATUS mandatory
			DESCRIPTION
				"Link Status:
				============
				This indicates the link status of the selected port
				
				1 - Link is down
				2 - Link is Up"
			::= { oslam8g-portStatus 1 }

		
		-- 1.3.6.1.4.1.11606.4.2.5.2
		oslam8gPortDuplexStatus OBJECT-TYPE
			SYNTAX INTEGER
				{
				halfDuplex(1),
				fullDuplex(2)
				}
			ACCESS read-only
			STATUS mandatory
			DESCRIPTION
				"Duplex Mode:
				============
				Valid if link status is up.
				
				1 - Half-Duplex
				2 - Full-Duplex"
			::= { oslam8g-portStatus 2 }

		
		-- 1.3.6.1.4.1.11606.4.2.5.3
		oslam8gPortSpeedStatus OBJECT-TYPE
			SYNTAX INTEGER
				{
				speed10Mbps(1),
				speed100MBps(2),
				speed1000MBps(3),
				speedReserved(4)
				}
			ACCESS read-only
			STATUS mandatory
			DESCRIPTION
				"Speed Mode:
				===========
				Valid if link status is up.
				
				1 - 10MBps
				2 - 100MBps
				3 - 1000MBps
				4 - Reserved for future used"
			::= { oslam8g-portStatus 3 }

		
-- OSLAM-8G Port Counters
		-- 1.3.6.1.4.1.11606.4.2.6
		oslam8g-portRMON OBJECT IDENTIFIER ::= { oslam8g-Port 6 }

		
		-- 1.3.6.1.4.1.11606.4.2.6.1
		oslam8gPortRMONIngress OBJECT IDENTIFIER ::= { oslam8g-portRMON 1 }

		
		-- 1.3.6.1.4.1.11606.4.2.6.1.1
		oslam8gPortInGoodOctetsLo OBJECT-TYPE
			SYNTAX Counter
			ACCESS read-only
			STATUS mandatory
			::= { oslam8gPortRMONIngress 1 }

		
		-- 1.3.6.1.4.1.11606.4.2.6.1.2
		oslam8gPortInGoodOctetsHi OBJECT-TYPE
			SYNTAX Counter
			ACCESS read-only
			STATUS mandatory
			::= { oslam8gPortRMONIngress 2 }

		
		-- 1.3.6.1.4.1.11606.4.2.6.1.3
		oslam8gPortInBadOctets OBJECT-TYPE
			SYNTAX Counter
			ACCESS read-only
			STATUS mandatory
			::= { oslam8gPortRMONIngress 3 }

		
		-- 1.3.6.1.4.1.11606.4.2.6.1.4
		oslam8gPortInUnicast OBJECT-TYPE
			SYNTAX Counter
			ACCESS read-only
			STATUS mandatory
			::= { oslam8gPortRMONIngress 4 }

		
		-- 1.3.6.1.4.1.11606.4.2.6.1.5
		oslam8gPortInBroadcasts OBJECT-TYPE
			SYNTAX Counter
			ACCESS read-only
			STATUS mandatory
			::= { oslam8gPortRMONIngress 5 }

		
		-- 1.3.6.1.4.1.11606.4.2.6.1.6
		oslam8gPortInMulticasts OBJECT-TYPE
			SYNTAX Counter
			ACCESS read-only
			STATUS mandatory
			::= { oslam8gPortRMONIngress 6 }

		
		-- 1.3.6.1.4.1.11606.4.2.6.1.7
		oslam8gPortInPause OBJECT-TYPE
			SYNTAX Counter
			ACCESS read-only
			STATUS mandatory
			::= { oslam8gPortRMONIngress 7 }

		
		-- 1.3.6.1.4.1.11606.4.2.6.1.8
		oslam8gPortInUndersize OBJECT-TYPE
			SYNTAX Counter
			ACCESS read-only
			STATUS mandatory
			::= { oslam8gPortRMONIngress 8 }

		
		-- 1.3.6.1.4.1.11606.4.2.6.1.9
		oslam8gPortInFragments OBJECT-TYPE
			SYNTAX Counter
			ACCESS read-only
			STATUS mandatory
			::= { oslam8gPortRMONIngress 9 }

		
		-- 1.3.6.1.4.1.11606.4.2.6.1.10
		oslam8gPortInOversize OBJECT-TYPE
			SYNTAX Counter
			ACCESS read-only
			STATUS mandatory
			::= { oslam8gPortRMONIngress 10 }

		
		-- 1.3.6.1.4.1.11606.4.2.6.1.11
		oslam8gPortInJabber OBJECT-TYPE
			SYNTAX Counter
			ACCESS read-only
			STATUS mandatory
			::= { oslam8gPortRMONIngress 11 }

		
		-- 1.3.6.1.4.1.11606.4.2.6.1.12
		oslam8gPortInRxErr OBJECT-TYPE
			SYNTAX Counter
			ACCESS read-only
			STATUS mandatory
			::= { oslam8gPortRMONIngress 12 }

		
		-- 1.3.6.1.4.1.11606.4.2.6.1.13
		oslam8gPortInFCSErr OBJECT-TYPE
			SYNTAX Counter
			ACCESS read-only
			STATUS mandatory
			::= { oslam8gPortRMONIngress 13 }

		
		-- 1.3.6.1.4.1.11606.4.2.6.1.14
		oslam8gPortInDiscards OBJECT-TYPE
			SYNTAX Counter
			ACCESS read-only
			STATUS mandatory
			::= { oslam8gPortRMONIngress 14 }

		
		-- 1.3.6.1.4.1.11606.4.2.6.1.15
		oslam8gPortInFiltered OBJECT-TYPE
			SYNTAX Counter
			ACCESS read-only
			STATUS mandatory
			::= { oslam8gPortRMONIngress 15 }

		
		-- 1.3.6.1.4.1.11606.4.2.6.2
		oslam8gPortRMONEgress OBJECT IDENTIFIER ::= { oslam8g-portRMON 2 }

		
		-- 1.3.6.1.4.1.11606.4.2.6.2.1
		oslam8gPortOutOctetsLo OBJECT-TYPE
			SYNTAX Counter
			ACCESS read-only
			STATUS mandatory
			::= { oslam8gPortRMONEgress 1 }

		
		-- 1.3.6.1.4.1.11606.4.2.6.2.2
		oslam8gPortOutOctetsHi OBJECT-TYPE
			SYNTAX Counter
			ACCESS read-only
			STATUS mandatory
			::= { oslam8gPortRMONEgress 2 }

		
		-- 1.3.6.1.4.1.11606.4.2.6.2.3
		oslam8gPortOutUnicast OBJECT-TYPE
			SYNTAX Counter
			ACCESS read-only
			STATUS mandatory
			::= { oslam8gPortRMONEgress 3 }

		
		-- 1.3.6.1.4.1.11606.4.2.6.2.4
		oslam8gPortOutBroadcasts OBJECT-TYPE
			SYNTAX Counter
			ACCESS read-only
			STATUS mandatory
			::= { oslam8gPortRMONEgress 4 }

		
		-- 1.3.6.1.4.1.11606.4.2.6.2.5
		oslam8gPortOutMulticasts OBJECT-TYPE
			SYNTAX Counter
			ACCESS read-only
			STATUS mandatory
			::= { oslam8gPortRMONEgress 5 }

		
		-- 1.3.6.1.4.1.11606.4.2.6.2.6
		oslam8gPortOutPause OBJECT-TYPE
			SYNTAX Counter
			ACCESS read-only
			STATUS mandatory
			::= { oslam8gPortRMONEgress 6 }

		
		-- 1.3.6.1.4.1.11606.4.2.6.2.7
		oslam8gPortOutExcessive OBJECT-TYPE
			SYNTAX Counter
			ACCESS read-only
			STATUS mandatory
			::= { oslam8gPortRMONEgress 7 }

		
		-- 1.3.6.1.4.1.11606.4.2.6.2.8
		oslam8gPortOutCollisions OBJECT-TYPE
			SYNTAX Counter
			ACCESS read-only
			STATUS mandatory
			::= { oslam8gPortRMONEgress 8 }

		
		-- 1.3.6.1.4.1.11606.4.2.6.2.9
		oslam8gPortOutDeferred OBJECT-TYPE
			SYNTAX Counter
			ACCESS read-only
			STATUS mandatory
			::= { oslam8gPortRMONEgress 9 }

		
		-- 1.3.6.1.4.1.11606.4.2.6.2.10
		oslam8gPortOutSingle OBJECT-TYPE
			SYNTAX Counter
			ACCESS read-only
			STATUS mandatory
			::= { oslam8gPortRMONEgress 10 }

		
		-- 1.3.6.1.4.1.11606.4.2.6.2.11
		oslam8gPortOutMultiple OBJECT-TYPE
			SYNTAX Counter
			ACCESS read-only
			STATUS mandatory
			::= { oslam8gPortRMONEgress 11 }

		
		-- 1.3.6.1.4.1.11606.4.2.6.2.12
		oslam8gPortOutFCSErr OBJECT-TYPE
			SYNTAX Counter
			ACCESS read-only
			STATUS mandatory
			::= { oslam8gPortRMONEgress 12 }

		
		-- 1.3.6.1.4.1.11606.4.2.6.2.13
		oslam8gPortOutLate OBJECT-TYPE
			SYNTAX Counter
			ACCESS read-only
			STATUS mandatory
			::= { oslam8gPortRMONEgress 13 }

		
		-- 1.3.6.1.4.1.11606.4.2.6.2.14
		oslam8gPortOutFiltered OBJECT-TYPE
			SYNTAX Counter
			ACCESS read-only
			STATUS mandatory
			::= { oslam8gPortRMONEgress 14 }

		
		-- 1.3.6.1.4.1.11606.4.2.6.3
		oslam8gPortHistogram OBJECT IDENTIFIER ::= { oslam8g-portRMON 3 }

		
		-- 1.3.6.1.4.1.11606.4.2.6.3.1
		oslam8gPortHistogramMode OBJECT-TYPE
			SYNTAX INTEGER
				{
				countRxFramesOnly(1),
				countTxFramesOnly(2),
				countRxTxFrames(3)
				}
			ACCESS read-write
			STATUS mandatory
			DESCRIPTION
				"Histogram Counters Mode:
				========================
				The Histogram mode control how the Histogram counters work as follows.
				
				1 - Count received frames only
				2 - Count transmitted frames only
				3 - Count receive and tranmitted frames"
			::= { oslam8gPortHistogram 1 }

		
		-- 1.3.6.1.4.1.11606.4.2.6.3.2
		oslam8gPortOut64Octets OBJECT-TYPE
			SYNTAX Counter
			ACCESS read-only
			STATUS mandatory
			::= { oslam8gPortHistogram 2 }

		
		-- 1.3.6.1.4.1.11606.4.2.6.3.3
		oslam8gPortOut65to127Octets OBJECT-TYPE
			SYNTAX Counter
			ACCESS read-only
			STATUS mandatory
			::= { oslam8gPortHistogram 3 }

		
		-- 1.3.6.1.4.1.11606.4.2.6.3.4
		oslam8gPortOut128to255Octets OBJECT-TYPE
			SYNTAX Counter
			ACCESS read-only
			STATUS mandatory
			::= { oslam8gPortHistogram 4 }

		
		-- 1.3.6.1.4.1.11606.4.2.6.3.5
		oslam8gPortOut256to511Octets OBJECT-TYPE
			SYNTAX Counter
			ACCESS read-only
			STATUS mandatory
			::= { oslam8gPortHistogram 5 }

		
		-- 1.3.6.1.4.1.11606.4.2.6.3.6
		oslam8gPortOut512to1023Octets OBJECT-TYPE
			SYNTAX Counter
			ACCESS read-only
			STATUS mandatory
			::= { oslam8gPortHistogram 6 }

		
		-- 1.3.6.1.4.1.11606.4.2.6.3.7
		oslam8gPortOut1024toMaxOctets OBJECT-TYPE
			SYNTAX Counter
			ACCESS read-only
			STATUS mandatory
			::= { oslam8gPortHistogram 7 }

		
		-- 1.3.6.1.4.1.11606.5
		fpcm OBJECT IDENTIFIER ::= { pbn 5 }

		
		-- 1.3.6.1.4.1.11606.5.1
		targetNodeAddress OBJECT-TYPE
			SYNTAX OCTET STRING (SIZE (10))
			ACCESS read-write
			STATUS mandatory
			DESCRIPTION
				"Target Node Address:
				====================
				FPCM is a broadcast device. 10 digits decimal address required to
				access the target optical node. Value of 4294967295 represent a broadcast
				address i.e. message will be send to all connected node.
				This value is the serial number of the ODN4P-ABC."
			::= { fpcm 1 }

		
-- Access Control for ODN4P node
		-- 1.3.6.1.4.1.11606.5.2
		odn4pAccess OBJECT IDENTIFIER ::= { fpcm 2 }

		
		-- 1.3.6.1.4.1.11606.5.2.1
		odn4pABSwitchingMode OBJECT-TYPE
			SYNTAX INTEGER
				{
				manual(1),
				automatic(2)
				}
			ACCESS read-write
			STATUS mandatory
			DESCRIPTION
				"AB Switching Mode:
				==================
				The mode of operation for ODN4P-AB. Available operation mode are:
				- AUTOMATIC
				- MANUAL"
			::= { odn4pAccess 1 }

		
		-- 1.3.6.1.4.1.11606.5.2.2
		odn4pChannelSelect OBJECT-TYPE
			SYNTAX INTEGER
				{
				priOpt(1),
				secOpt(2)
				}
			ACCESS read-write
			STATUS mandatory
			DESCRIPTION
				"Channel Select:
				===============
				The channel to be selected by the AB redundancy switch.
				Upon changing the channel, AB operation mode at the target
				device will change to MANUAL mode automatically."
			::= { odn4pAccess 2 }

		
		-- 1.3.6.1.4.1.11606.5.2.3
		odn4pSwitchingHysteresis OBJECT-TYPE
			SYNTAX INTEGER
				{
				neg3dot5dBmV(0),
				neg3dot0dBmV(1),
				neg2dot5dBmV(2),
				neg2dot0dBmV(3),
				neg1dot5dBmV(4),
				neg1dot0dBmV(5),
				neg0dot5dBmV(6),
				neg0dot0dBmV(7)
				}
			ACCESS read-write
			STATUS mandatory
			DESCRIPTION
				"Switch Hysteresis:
				==================
				Primary Optical recovery level."
			::= { odn4pAccess 3 }

		
		-- 1.3.6.1.4.1.11606.5.2.4
		odn4pPrimarySwitchOverTime OBJECT-TYPE
			SYNTAX INTEGER (1..15)
			ACCESS read-write
			STATUS mandatory
			DESCRIPTION
				"Primary switch-over time:
				=========================
				The number of second wait required before change of state"
			::= { odn4pAccess 4 }

		
		-- 1.3.6.1.4.1.11606.5.2.5
		odn4pSecondarySwitchOverTime OBJECT-TYPE
			SYNTAX INTEGER (1..15)
			ACCESS read-write
			STATUS mandatory
			DESCRIPTION
				"Secondary switch-over time:
				===========================
				The number of second wait required before change of state"
			::= { odn4pAccess 5 }

		
		-- 1.3.6.1.4.1.11606.5.2.6
		odn4pAttenuator1 OBJECT-TYPE
			SYNTAX INTEGER (2..40)
			ACCESS read-write
			STATUS mandatory
			DESCRIPTION
				"Attenuator 1:
				=============
				Attenuation used for ingress control.
				Unit is in 1dB step.
				Acceptable value range: 2-40dB"
			::= { odn4pAccess 6 }

		
		-- 1.3.6.1.4.1.11606.5.2.7
		odn4pAttenuator2 OBJECT-TYPE
			SYNTAX INTEGER (2..40)
			ACCESS read-write
			STATUS mandatory
			DESCRIPTION
				"Attenuator 2:
				=============
				Attenuation used for ingress control.
				Unit is in 1dB step.
				Acceptable value range: 2-40dB"
			::= { odn4pAccess 7 }

		
		-- 1.3.6.1.4.1.11606.5.2.8
		odn4pAttenuator3 OBJECT-TYPE
			SYNTAX INTEGER (2..40)
			ACCESS read-write
			STATUS mandatory
			DESCRIPTION
				"Attenuator 3:
				=============
				Attenuation used for ingress control.
				Unit is in 1dB step.
				Acceptable value range: 2-40dB"
			::= { odn4pAccess 8 }

		
		-- 1.3.6.1.4.1.11606.5.2.9
		odn4pAttenuator4 OBJECT-TYPE
			SYNTAX INTEGER (2..40)
			ACCESS read-write
			STATUS mandatory
			DESCRIPTION
				"Attenuator 4:
				=============
				Attenuation used for ingress control.
				Unit is in 1dB step.
				Acceptable value range: 2-40dB"
			::= { odn4pAccess 9 }

		
		-- 1.3.6.1.4.1.11606.5.2.10
		odn4pHomeFskChannel OBJECT-TYPE
			SYNTAX INTEGER (0..100)
			ACCESS read-write
			STATUS mandatory
			DESCRIPTION
				"Remote node FSK home channel:
				=============================
				Each network may use different default FSK channel.
				This is the default FSK channel to be managed by operator.
				Optical node always tune to home channel prior to agility."
			::= { odn4pAccess 10 }

		
		-- 1.3.6.1.4.1.11606.5.2.11
		odn4pFskMode OBJECT-TYPE
			SYNTAX INTEGER
				{
				fskFix(1),
				fskAgile(2)
				}
			ACCESS read-write
			STATUS mandatory
			DESCRIPTION
				"FSK Operating mode
				==================
				Force FSK to operate in either FIX or AGILE mode.
				FIX - FSK receiver always try to lock to the known FSK frequency
				AGILE - Always search for an FSK channel that is capable of decoding data
				"
			::= { odn4pAccess 11 }

		
		-- 1.3.6.1.4.1.11606.5.2.12
		odn4pLoopTest OBJECT-TYPE
			SYNTAX INTEGER
				{
				uidSrcAddr0(22),
				uidSrcAddr1(23),
				uidSrcAddr2(24),
				uidSrcAddr3(25),
				uidAddr0(26),
				uidAddr1(27),
				uidAddr2(28),
				uidAddr3(29),
				uidMajorVer(30),
				uidMinorVer(31),
				uidAtten0(33),
				uidAtten1(34),
				uidAtten2(35),
				uidAtten3(36),
				uidFSKCh(48),
				uidFSKMode(50),
				uidPassTest112(112),
				uidPassTest113(113),
				uidPassTest114(114),
				uidPassTest115(115),
				uidPassTest116(116),
				uidPassTest117(117),
				uidPassTest118(118),
				uidPassTest119(119),
				uidPassTest120(120),
				uidPassTest121(121),
				uidPassTest122(122),
				uidPassTest123(123),
				uidPassTest124(124),
				uidPassTest125(125),
				uidPassTest126(126),
				uidPassTest127(127),
				uidModeSel(129),
				uidInpSel(130),
				uidPriRefLvl(131),
				uidPriSwtTime(132),
				uidSecSwtTime(133),
				uidModeChgCnt(134),
				uidInpChgCnt(135),
				uidClearTest(251)
				}
			ACCESS read-write
			STATUS mandatory
			DESCRIPTION
				"ODN4P LOOP TEST
				===============
				Acceptable value is 0-255 or 8-bit number.
				Value between between 1..255 will be display on the connected 
				RPQRM of the selected channel if this OID has been iniated.
				Set value to 0xFB will clear loopback test and normal data will 
				then be seen in the RPQRM.
				Operator should only use value between 0x70 to 0x7F for testing
				Other values are reserved for NETCRAFT
				
				"
			::= { odn4pAccess 12 }

		
-- Node Access Control:
-- ====================
-- This usually used by remote management software (NMS3)
-- Operator should ignore or do not change these OID value.
		-- 1.3.6.1.4.1.11606.5.3
		nodeAccess OBJECT IDENTIFIER ::= { fpcm 3 }

		
		-- 1.3.6.1.4.1.11606.5.3.1
		nodeAccessDataLength OBJECT-TYPE
			SYNTAX INTEGER
			ACCESS read-write
			STATUS mandatory
			DESCRIPTION
				"Node Access Control Data Length:
				================================
				This usually used by remote management software (NMS3)
				Operator should ignore or do not change this OID value."
			::= { nodeAccess 1 }

		
		-- 1.3.6.1.4.1.11606.5.3.2
		nodeAccessData OBJECT-TYPE
			SYNTAX Opaque (SIZE (0..32))
			ACCESS read-write
			STATUS mandatory
			DESCRIPTION
				"Node Access Control Data:
				=========================
				This usually used by remote management software (NMS3)
				Operator should ignore or do not change this OID value."
			::= { nodeAccess 2 }

		
		-- 1.3.6.1.4.1.11606.5.3.3
		nodeAccessCmd OBJECT-TYPE
			SYNTAX INTEGER (0..255)
			ACCESS read-write
			STATUS mandatory
			DESCRIPTION
				"Node Access Control Command:
				============================
				This usually used by remote management software (NMS3)
				Operator should ignore or do not change this OID value."
			::= { nodeAccess 3 }

		
-- FPCM FSK Modulation Control
		-- 1.3.6.1.4.1.11606.5.4
		fpcmCtrl OBJECT IDENTIFIER ::= { fpcm 4 }

		
		-- 1.3.6.1.4.1.11606.5.4.1
		fpcmFSKChannel OBJECT-TYPE
			SYNTAX INTEGER (0..100)
			ACCESS read-write
			STATUS mandatory
			DESCRIPTION
				"FSK Channel modulated by FPCM:
				==============================
				Acceptable FSK channel range 0-100.
				FSK modulation range 80-90MHz (Channel 0-100 respectively)"
			::= { fpcmCtrl 1 }

		
		-- 1.3.6.1.4.1.11606.5.4.2
		fpcmRFLevel OBJECT-TYPE
			SYNTAX INTEGER (25..45)
			ACCESS read-write
			STATUS mandatory
			DESCRIPTION
				"FPCM RF level
				=============
				RF level setting in 1dBmV scale.
				Current supported value is 25-45dBmV"
			::= { fpcmCtrl 2 }

		
		-- 1.3.6.1.4.1.11606.6
		mau OBJECT IDENTIFIER ::= { pbn 6 }

		
-- Product Information Tree
		-- 1.3.6.1.4.1.11606.6.1
		mauProductInfo OBJECT IDENTIFIER ::= { mau 1 }

		
		-- 1.3.6.1.4.1.11606.6.1.1
		mauProductModelName OBJECT-TYPE
			SYNTAX OCTET STRING
			ACCESS read-only
			STATUS mandatory
			DESCRIPTION
				"Product model name"
			::= { mauProductInfo 1 }

		
		-- 1.3.6.1.4.1.11606.6.1.2
		mauProductVersion OBJECT-TYPE
			SYNTAX OCTET STRING
			ACCESS read-only
			STATUS mandatory
			DESCRIPTION
				"Product version number"
			::= { mauProductInfo 2 }

		
		-- 1.3.6.1.4.1.11606.6.1.3
		mauProductVersionDate OBJECT-TYPE
			SYNTAX OCTET STRING
			ACCESS read-only
			STATUS mandatory
			DESCRIPTION
				"Product build date"
			::= { mauProductInfo 3 }

		
		-- 1.3.6.1.4.1.11606.6.1.4
		mauProductMAC OBJECT-TYPE
			SYNTAX OCTET STRING (SIZE (6))
			ACCESS read-only
			STATUS mandatory
			::= { mauProductInfo 4 }

		
		-- 1.3.6.1.4.1.11606.6.1.5
		mauProductSerialNumber OBJECT-TYPE
			SYNTAX OCTET STRING (SIZE (6))
			ACCESS read-only
			STATUS mandatory
			::= { mauProductInfo 5 }

		
-- Monitoring OID which is read-only.
		-- 1.3.6.1.4.1.11606.6.2
		mauStatus OBJECT IDENTIFIER ::= { mau 2 }

		
		-- 1.3.6.1.4.1.11606.6.2.1
		mauStatusVACType OBJECT-TYPE
			SYNTAX TypePowerSupply
			ACCESS read-only
			STATUS mandatory
			DESCRIPTION
				"VAC input type. e.g. '220V'"
			::= { mauStatus 1 }

		
		-- 1.3.6.1.4.1.11606.6.2.2
		mauStatus5V OBJECT-TYPE
			SYNTAX OCTET STRING
			ACCESS read-only
			STATUS mandatory
			DESCRIPTION
				"+5V supply voltage level. 
				Unit is in Volt e.g. 4.92V"
			::= { mauStatus 2 }

		
		-- 1.3.6.1.4.1.11606.6.2.3
		mauStatus12V OBJECT-TYPE
			SYNTAX OCTET STRING
			ACCESS read-only
			STATUS mandatory
			DESCRIPTION
				"+12V supply voltage level. 
				Unit is in Volt e.g. 12.00V"
			::= { mauStatus 3 }

		
		-- 1.3.6.1.4.1.11606.6.2.4
		mauStatus24V OBJECT-TYPE
			SYNTAX OCTET STRING
			ACCESS read-only
			STATUS mandatory
			DESCRIPTION
				"+24V supply voltage level. 
				Unit is in Volt e.g. 24.10V"
			::= { mauStatus 4 }

		
		-- 1.3.6.1.4.1.11606.6.2.5
		mauStatusInputOpticalPower OBJECT-TYPE
			SYNTAX OCTET STRING
			ACCESS read-only
			STATUS mandatory
			DESCRIPTION
				"Optical input power level.
				Unit is in dBm e.g. -2.05dBm"
			::= { mauStatus 5 }

		
		-- 1.3.6.1.4.1.11606.6.2.6
		mauStatusOutputOpticalPower OBJECT-TYPE
			SYNTAX OCTET STRING
			ACCESS read-only
			STATUS mandatory
			DESCRIPTION
				"Optical input power level.
				Unit is in dBm e.g. -2.05dBm"
			::= { mauStatus 6 }

		
		-- 1.3.6.1.4.1.11606.6.2.7
		mauStatusRFOutputPower OBJECT-TYPE
			SYNTAX OCTET STRING
			ACCESS read-only
			STATUS mandatory
			DESCRIPTION
				"Total RF output power level.
				Unit is in dBmV e.g. 41.23dBmV total or 25.00dBmV/Ch@42Ch."
			::= { mauStatus 7 }

		
		-- 1.3.6.1.4.1.11606.6.2.8
		mauStatusTemperature OBJECT-TYPE
			SYNTAX OCTET STRING
			ACCESS read-only
			STATUS mandatory
			DESCRIPTION
				"Module internal temperature. 
				Unit is in Degree Celsius e.g. 29.25C"
			::= { mauStatus 8 }

		
		-- 1.3.6.1.4.1.11606.6.2.9
		mauStatusLid OBJECT-TYPE
			SYNTAX TypeTamper
			ACCESS read-only
			STATUS mandatory
			DESCRIPTION
				"Device lid open/close status"
			::= { mauStatus 9 }

		
		-- 1.3.6.1.4.1.11606.6.2.10
		mauStatusONUInstalled OBJECT-TYPE
			SYNTAX TypeYesNo
			ACCESS read-only
			STATUS mandatory
			DESCRIPTION
				"EPON-ONU installed status."
			::= { mauStatus 10 }

		
		-- 1.3.6.1.4.1.11606.6.2.11
		mauStatusMOCAInstalled OBJECT-TYPE
			SYNTAX TypeYesNo
			ACCESS read-only
			STATUS mandatory
			DESCRIPTION
				"MOCA installed status."
			::= { mauStatus 11 }

		
		-- 1.3.6.1.4.1.11606.6.2.12
		mauStatusPLCInstalled OBJECT-TYPE
			SYNTAX TypeYesNo
			ACCESS read-only
			STATUS mandatory
			DESCRIPTION
				"PLC installed status."
			::= { mauStatus 12 }

		
		-- 1.3.6.1.4.1.11606.6.2.13
		mauStatusLED OBJECT-TYPE
			SYNTAX TypeOnOff
			ACCESS read-only
			STATUS mandatory
			DESCRIPTION
				"Status LED"
			::= { mauStatus 13 }

		
		-- 1.3.6.1.4.1.11606.6.2.14
		mauStatusGainControlLED OBJECT-TYPE
			SYNTAX TypeOnOff
			ACCESS read-only
			STATUS mandatory
			DESCRIPTION
				"Gain control LED (AGC/MGC) status.
				ON  - AGC mode
				OFF - MGC mode"
			::= { mauStatus 14 }

		
		-- 1.3.6.1.4.1.11606.6.2.15
		mauStatusOpticalInputHighLED OBJECT-TYPE
			SYNTAX TypeOnOff
			ACCESS read-only
			STATUS mandatory
			DESCRIPTION
				"Optical input high led indicator
				ON  - Optical input is too high."
			::= { mauStatus 15 }

		
		-- 1.3.6.1.4.1.11606.6.2.16
		mauStatusOpticalInputLowLED OBJECT-TYPE
			SYNTAX TypeOnOff
			ACCESS read-only
			STATUS mandatory
			DESCRIPTION
				"Optical input LOW led indicator
				ON  - Optical input is too low."
			::= { mauStatus 16 }

		
		-- 1.3.6.1.4.1.11606.6.2.17
		mauStatus5VMin OBJECT-TYPE
			SYNTAX DisplayString
			ACCESS read-only
			STATUS mandatory
			DESCRIPTION
				"+5V Supply MIN voltage alarm level"
			::= { mauStatus 17 }

		
		-- 1.3.6.1.4.1.11606.6.2.18
		mauStatus5VMax OBJECT-TYPE
			SYNTAX DisplayString
			ACCESS read-only
			STATUS mandatory
			DESCRIPTION
				"+5V Supply MAX voltage alarm level"
			::= { mauStatus 18 }

		
		-- 1.3.6.1.4.1.11606.6.2.19
		mauStatus12VMin OBJECT-TYPE
			SYNTAX DisplayString
			ACCESS read-only
			STATUS mandatory
			DESCRIPTION
				"+12V Supply MIN voltage alarm level"
			::= { mauStatus 19 }

		
		-- 1.3.6.1.4.1.11606.6.2.20
		mauStatus12VMax OBJECT-TYPE
			SYNTAX DisplayString
			ACCESS read-only
			STATUS mandatory
			DESCRIPTION
				"+12V Supply MAX voltage alarm level"
			::= { mauStatus 20 }

		
		-- 1.3.6.1.4.1.11606.6.2.21
		mauStatus24VMin OBJECT-TYPE
			SYNTAX DisplayString
			ACCESS read-only
			STATUS mandatory
			DESCRIPTION
				"+24V Supply MIN voltage alarm level"
			::= { mauStatus 21 }

		
		-- 1.3.6.1.4.1.11606.6.2.22
		mauStatus24VMax OBJECT-TYPE
			SYNTAX DisplayString
			ACCESS read-only
			STATUS mandatory
			DESCRIPTION
				"+24V Supply MAX voltage alarm level"
			::= { mauStatus 22 }

		
		-- 1.3.6.1.4.1.11606.6.2.23
		mauStatusInputOpticalPowerMin OBJECT-TYPE
			SYNTAX DisplayString
			ACCESS read-only
			STATUS mandatory
			DESCRIPTION
				"Optical Input Power MIN alarm level"
			::= { mauStatus 23 }

		
		-- 1.3.6.1.4.1.11606.6.2.24
		mauStatusInputOpticalPowerMax OBJECT-TYPE
			SYNTAX DisplayString
			ACCESS read-only
			STATUS mandatory
			DESCRIPTION
				"Optical Input Power MAX alarm level"
			::= { mauStatus 24 }

		
		-- 1.3.6.1.4.1.11606.6.2.25
		mauStatusOutputOpticalPowerMin OBJECT-TYPE
			SYNTAX DisplayString
			ACCESS read-only
			STATUS mandatory
			DESCRIPTION
				"Optical Output Power MIN alarm level"
			::= { mauStatus 25 }

		
		-- 1.3.6.1.4.1.11606.6.2.26
		mauStatusOutputOpticalPowerMax OBJECT-TYPE
			SYNTAX DisplayString
			ACCESS read-only
			STATUS mandatory
			DESCRIPTION
				"Optical Output Power MAX alarm level"
			::= { mauStatus 26 }

		
		-- 1.3.6.1.4.1.11606.6.2.27
		mauStatusTemperatureMin OBJECT-TYPE
			SYNTAX DisplayString
			ACCESS read-only
			STATUS mandatory
			DESCRIPTION
				"Temperature MIN alarm level"
			::= { mauStatus 27 }

		
		-- 1.3.6.1.4.1.11606.6.2.28
		mauStatusTemperatureMax OBJECT-TYPE
			SYNTAX DisplayString
			ACCESS read-only
			STATUS mandatory
			DESCRIPTION
				"Temperature MAX alarm level"
			::= { mauStatus 28 }

		
		-- 1.3.6.1.4.1.11606.6.2.29
		mauStatusGainControlMin OBJECT-TYPE
			SYNTAX DisplayString
			ACCESS read-only
			STATUS mandatory
			DESCRIPTION
				"Gain Control MIN Level"
			::= { mauStatus 29 }

		
		-- 1.3.6.1.4.1.11606.6.2.30
		mauStatusGainControlMax OBJECT-TYPE
			SYNTAX DisplayString
			ACCESS read-only
			STATUS mandatory
			DESCRIPTION
				"Gain Control MAX Level"
			::= { mauStatus 30 }

		
		-- 1.3.6.1.4.1.11606.6.2.31
		mauStatusAgcLock OBJECT-TYPE
			SYNTAX TypeAGCStatus
			ACCESS read-only
			STATUS mandatory
			DESCRIPTION
				"AGC lock when the controlled signal is within range.
				AGC unlock when agc cannot control the signal or signal is out of range for AGC to operate."
			::= { mauStatus 31 }

		
		-- 1.3.6.1.4.1.11606.6.3
		mauControl OBJECT IDENTIFIER ::= { mau 3 }

		
		-- 1.3.6.1.4.1.11606.6.3.1
		mauGainControlMode OBJECT-TYPE
			SYNTAX TypeGainMode
			ACCESS read-write
			STATUS mandatory
			DESCRIPTION
				"RF gain control setting.
				1dB control step. 
				Control range to be adviced."
			::= { mauControl 1 }

		
		-- 1.3.6.1.4.1.11606.6.3.2
		mauTrapEnabled OBJECT-TYPE
			SYNTAX INTEGER
				{
				trapDisabled(1),
				trapEnabled(2)
				}
			ACCESS read-write
			STATUS mandatory
			DESCRIPTION
				"Indicates if this trap entry is enabled or not."
			::= { mauControl 2 }

		
		-- 1.3.6.1.4.1.11606.6.3.3
		mauPrimaryCommunity OBJECT-TYPE
			SYNTAX DisplayString
			ACCESS read-write
			STATUS mandatory
			DESCRIPTION
				"Primary Community String to be used by agent for SNMP GET/SET for mauTrapPrimaryReceiverIPAddress"
			::= { mauControl 3 }

		
		-- 1.3.6.1.4.1.11606.6.3.4
		mauSecondaryCommunity OBJECT-TYPE
			SYNTAX DisplayString
			ACCESS read-write
			STATUS mandatory
			DESCRIPTION
				"Secondary Community String to be used by agent for SNMP GET/SET for mauTrapSecondaryReceiverIPAddress"
			::= { mauControl 4 }

		
		-- 1.3.6.1.4.1.11606.6.3.5
		mauPrimaryTrapReceiverIPAddress OBJECT-TYPE
			SYNTAX IpAddress
			ACCESS read-write
			STATUS mandatory
			DESCRIPTION
				"The primary Trap Receiver station IP address"
			::= { mauControl 5 }

		
		-- 1.3.6.1.4.1.11606.6.3.6
		mauSecondaryTrapReceiverIPAddress OBJECT-TYPE
			SYNTAX IpAddress
			ACCESS read-write
			STATUS mandatory
			DESCRIPTION
				"The secondary Trap Receiver station IP address"
			::= { mauControl 6 }

		
		-- 1.3.6.1.4.1.11606.6.4
		mauTraps OBJECT IDENTIFIER ::= { mau 4 }

		
		-- 1.3.6.1.4.1.11606.6.4.1
		mauTrapMessageDescr OBJECT-TYPE
			SYNTAX DisplayString
			ACCESS read-write
			STATUS mandatory
			::= { mauTraps 1 }
                                 
                                 
		-- 1.3.6.1.4.1.11606.7
		lte153 OBJECT IDENTIFIER ::= { pbn 7 }
		
-- Product Information Tree
		-- 1.3.6.1.4.1.11606.7.1
		lte153Laser OBJECT IDENTIFIER ::= { lte153 1 }    
		
		tagID                 OBJECT-TYPE
		    SYNTAX            OCTET STRING (SIZE(0..23))
		    MAX-ACCESS        read-write
		    STATUS            current
		    DESCRIPTION       "Displays the tag name of the device in human-readable format as set by user."
		    ::= { lte153Laser 1 }
		
		modelNumber           OBJECT-TYPE
		    SYNTAX            OCTET STRING (SIZE(0..23))
		    MAX-ACCESS        read-only
		    STATUS            current
		    DESCRIPTION       "Displays the name of the device model number in human-readable format as set from the factory."
		    ::= { lte153Laser 2 }
		
		mfgDate               OBJECT-TYPE
		    SYNTAX            OCTET STRING (SIZE(0..23))
		    MAX-ACCESS        read-only
		    STATUS            current
		    DESCRIPTION       "Displays the manufacturing date in human-readable format as set from the factory."
		    ::= { lte153Laser 3 }
		
		serialNum             OBJECT-TYPE
		    SYNTAX            OCTET STRING (SIZE(0..23))
		    MAX-ACCESS        read-only
		    STATUS            current
		    DESCRIPTION       "Displays the serial number in human-readable format as set from the factory."
		    ::= { lte153Laser 4 }
		
		firmwareRev           OBJECT-TYPE
		    SYNTAX            OCTET STRING (SIZE(0..23))
		    MAX-ACCESS        read-only
		    STATUS            current
		    DESCRIPTION       "Displays the software revision of the device in human-readable format."
		    ::= { lte153Laser 5 }
		
		engRev                OBJECT-TYPE
		    SYNTAX            OCTET STRING (SIZE(0..23))
		    MAX-ACCESS        read-only
		    STATUS            current
		    DESCRIPTION       "Displays the engineering revision in human-readable format as set from the factory."
		    ::= { lte153Laser 6 }
		
		systemTemp            OBJECT-TYPE
		    SYNTAX            Integer32(-500..1200)
		    UNITS             "tenth of a Celsius degree(C)"
		    MAX-ACCESS        read-only
		    STATUS            current
		    DESCRIPTION       "Returns the unit temperature."
		    ::= { lte153Laser 7 }
		
		laserCurrent          OBJECT-TYPE
		    SYNTAX            Integer32(0..1250)
		    UNITS             "milliampere(mA)"
		    MAX-ACCESS        read-only
		    STATUS            current
		    DESCRIPTION       "Returns measured laser bias current."
		    ::= { lte153Laser 8 }
		     
		laserTemperature      OBJECT-TYPE
		    SYNTAX            Integer32(-500..800)
		    UNITS             "tenth of a Celsius degree(C)"
		    MAX-ACCESS        read-only
		    STATUS            current
		    DESCRIPTION       "Returns the measured laser temperature."
		    ::= { lte153Laser 9 }
		        
		inputRFLevel          OBJECT-TYPE
		    SYNTAX            Integer32(-1000..100)
		    UNITS             "tenth of a decibel(dB)"
		    MAX-ACCESS        read-only
		    STATUS            current
		    DESCRIPTION       "Returns the input RF level."
		    ::= { lte153Laser 10 }
		
		compositeRFLevel      OBJECT-TYPE
		    SYNTAX            Integer32(-1000..100)
		    UNITS             "tenth of a decibel(dB)"
		    MAX-ACCESS        read-only
		    STATUS            current
		    DESCRIPTION       "Returns the measured composite RF level." 
		    ::= { lte153Laser 11 }
		 
		opticalPowerOut1      OBJECT-TYPE
		    SYNTAX            Integer32(-1000..200)
		    UNITS             "tenth of decibel relative to one milliwatt(dBm)"
		    MAX-ACCESS        read-only
		    STATUS            current
		    DESCRIPTION       "Returns the optical power output for port 1."
		    ::= { lte153Laser 12 }
		
		opticalPowerOut2      OBJECT-TYPE
		    SYNTAX            Integer32(-1000..200)
		    UNITS             "tenth of decibel relative to one milliwatt(dBm)"
		    MAX-ACCESS        read-only
		    STATUS            current
		    DESCRIPTION       "Returns the optical power output for port 2."
		    ::= { lte153Laser 13 }
		
		tecCurrent            OBJECT-TYPE
		    SYNTAX            Integer32(-25000..25000)
		    UNITS             "milliampere(mA)"
		    MAX-ACCESS        read-only
		    STATUS            current
		    DESCRIPTION       "Returns the current of thermoelectric cooler inside the laser asssembly."
		    ::= { lte153Laser 14 }
		        
		attenuationSet        OBJECT-TYPE
		    SYNTAX            Integer32(-70..30)
		    UNITS             "tenth of a decibel(dB)"
		    MAX-ACCESS        read-write
		    STATUS            current
		    DESCRIPTION       "Manual mode RF attenuator setpoint." 
		    ::= { lte153Laser 15 }
		 
		omiSetpoint           OBJECT-TYPE
		    SYNTAX            Integer32(-30..30)
		    UNITS             "tenth of a decibel(dB)"
		    MAX-ACCESS        read-write
		    STATUS            current
		    DESCRIPTION       "Optical modulation index is implemented for CW or Video AGC modes as RF attenuator setpoint." 
		    ::= { lte153Laser 16 }
		 
		agcMode              OBJECT-TYPE
		    SYNTAX            INTEGER { undefined(0),manual(1),cw(2),video(3),invalidMode(4) }
		    UNITS             "no units"
		    MAX-ACCESS        read-write
		    STATUS            current
		    DESCRIPTION       "Returns the AGC mode." 
		    ::= { lte153Laser 17 }
		 
		sbsSuppression        OBJECT-TYPE
		    SYNTAX            Integer32(140..180)
		    UNITS             "tenth of a decibel relative to one milliwatt(dBm)"
		    MAX-ACCESS        read-write
		    STATUS            current
		    DESCRIPTION       "SBS suppression level." 
		    ::= { lte153Laser 18 }
		 
		fiberDispersionCntl   OBJECT-TYPE
		    SYNTAX            INTEGER { undefined(0),off(1),on(2) }
		    UNITS             "no units"
		    MAX-ACCESS        read-write
		    STATUS            current
		    DESCRIPTION       "Fiber dispersion compensation On/Off control." 
		    ::= { lte153Laser 19 }
		 
		fiberDispersionGain   OBJECT-TYPE
		    SYNTAX            Integer32(-40..40)
		    UNITS             "tenth of a volt"
		    MAX-ACCESS        read-write
		    STATUS            current
		    DESCRIPTION       "Fiber dispersion gain compensation." 
		    ::= { lte153Laser 20 }
		 
		fiberDispersionPhase  OBJECT-TYPE
		    SYNTAX            Integer32(-40..40)
		    UNITS             "tenth of a volt"
		    MAX-ACCESS        read-write
		    STATUS            current
		    DESCRIPTION       "Fiber dispersion phase compensation." 
		    ::= { lte153Laser 21 }
		 
		fiberDispersionSlope  OBJECT-TYPE
		    SYNTAX            Integer32(-40..40)
		    UNITS             "tenth of a volt"
		    MAX-ACCESS        read-write
		    STATUS            current
		    DESCRIPTION       "Fiber dispersion slope compensation." 
		    ::= { lte153Laser 22 }
		 
		laserOnOff            OBJECT-TYPE
		    SYNTAX            INTEGER { undefined(0),off(1),on(2) }
		    UNITS             "no units"
		    MAX-ACCESS        read-only
		    STATUS            current
		    DESCRIPTION       "returns the active laser On/Off status." 
		    ::= { lte153Laser 23 }
		 
		keyswitch             OBJECT-TYPE
		    SYNTAX            INTEGER { undefined(0),off(1),on(2) }
		    UNITS             "no units"
		    MAX-ACCESS        read-only
		    STATUS            current
		    DESCRIPTION       "Returns the status of the front panel keyswitch." 
		    ::= { lte153Laser 24 }
		 
		remoteLaserControl    OBJECT-TYPE
		    SYNTAX            INTEGER { undefined(0),off(1),on(2) }
		    UNITS             "no units"
		    MAX-ACCESS        read-write
		    STATUS            current
		    DESCRIPTION       "Remote laser On/Off control." 
		    ::= { lte153Laser 25 }
		 
		resetCause            OBJECT-TYPE
		    SYNTAX            INTEGER { undefined(0),other(1),powerup(2),command(3),watchdog(4),craft(5) }
		    UNITS             "no units"
		    MAX-ACCESS        read-only
		    STATUS            current
		    DESCRIPTION       "This object reports the cause of the last reset." 
		    ::= { lte153Laser 26 }
		 
		resetControl          OBJECT-TYPE
		    SYNTAX            INTEGER { undefined(0),reset(1) }
		    UNITS             "no units"
		    MAX-ACCESS        read-write
		    STATUS            current
		    DESCRIPTION       "This object is used to reset the transmitter module by writing a 1 to it.
		                       Other values written to the object have no effect.
		                       Reading the object returns a 1 and has no effect on the module.
		                      " 
		    ::= { lte153Laser 27 }
		 
		sbs2GHzPower          OBJECT-TYPE
		    SYNTAX            Integer32(-300..300)
		    UNITS             "tenth of a decibel relative to one milliwatt(dBm)"
		    MAX-ACCESS        read-only
		    STATUS            current
		    DESCRIPTION       "2GHz SBS output power level." 
		    ::= { lte153Laser 28 }
		 
		sbs6GHzPower          OBJECT-TYPE
		    SYNTAX            Integer32(-300..300)
		    UNITS             "tenth of a decibel relative to one milliwatt(dBm)"
		    MAX-ACCESS        read-only
		    STATUS            current
		    DESCRIPTION       "6GHz SBS output power level." 
		    ::= { lte153Laser 29 }
		 
		monitor5v             OBJECT-TYPE
		    SYNTAX            Integer32(0..70)
		    UNITS             "tenth of a volt(V)"
		    MAX-ACCESS        read-only
		    STATUS            current
		    DESCRIPTION       "Returns the measured value of the +5V supply."
		    ::= { lte153Laser 30 }    
		    
		monitor12v            OBJECT-TYPE
		    SYNTAX            Integer32(0..150)
		    UNITS             "tenth of a volt(V)"
		    MAX-ACCESS        read-only
		    STATUS            current
		    DESCRIPTION       "Returns the measured value of the +12V supply."
		    ::= { lte153Laser 31 }    
		    
		monitor24v            OBJECT-TYPE
		    SYNTAX            Integer32(0..300)
		    UNITS             "tenth of a volt(V)"
		    MAX-ACCESS        read-only
		    STATUS            current
		    DESCRIPTION       "Returns the measured value of the +24V supply."
		    ::= { lte153Laser 32 }    
		    
		monitorM5v            OBJECT-TYPE
		    SYNTAX            Integer32(-70..70)
		    UNITS             "tenth of a volt(V)"
		    MAX-ACCESS        read-only
		    STATUS            current
		    DESCRIPTION       "Returns the measured value of the -5V supply."
		    ::= { lte153Laser 33 }    
		    
		monitorM12v           OBJECT-TYPE
		    SYNTAX            Integer32(-150..150)
		    UNITS             "tenth of a volt(V)"
		    MAX-ACCESS        read-only
		    STATUS            current
		    DESCRIPTION       "Returns the measured value of the -12V supply."
		    ::= { lte153Laser 34 }    
		    
		unitStatusEnable      OBJECT-TYPE
		    SYNTAX            BITS 
		                      {
		                       systemTempHigh(0),
		                       systemTempLow(1),
		                       laserCurrentHigh(2),
		                       laserCurrentLow(3),
		                       laserTempHigh(4),
		                       laserTempLow(5),
		                       inputRFHigh(6),
		                       inputRFLow(7),
		                       opticalPowerHigh(8),
		                       opticalPowerLow(9),
		                       tecCurrentHigh(10),
		                       agcUnlock(11),
		                       keyInOffPosition(12),
		                       remoteOffModeSet(13)
		                      }
		    UNITS             "no units"
		    MAX-ACCESS        read-write
		    STATUS            current
		    DESCRIPTION       "Indicates the unit status alarm enable. This
		                       value is bit encoded therefore it is capable
		                       of indicating multiple alarm enable conditions. 
		                       The bits are defined as follows:
		
		                           0       1       2       3       4       5       6       7    
		                       +-------+-------+-------+-------+-------+-------+-------+-------+
		                       |System |System | Laser | Laser | Laser | Laser | Input | Input |
		                       | Temp  | Temp  |Current|Current| Temp  | Temp  |  RF   |  RF   |
		                       | High  | Low   | High  |  Low  | High  | Low   | Level | Level |
		                       |       |       |       |       |       |       |  High |  Low  |
		                       +-------+-------+-------+-------+-------+-------+-------+-------+
		
		                           8       9       10      11      12      13      14      15   
		                       +-------+-------+-------+-------+-------+-------+-------+-------+
		                       |Optical|Optical| TEC   |  AGC  |Key in |Remote |       |       |
		                       | Power | Power |Current| Unlock| Off   | Off   |       |       |
		                       |  Out  |  Out  | High  |       |Position Mode  |       |       |
		                       |  High |  Low  |       |       |       | Set   |       |       |
		                       +-------+-------+-------+-------+-------+-------+-------+-------+
		                      "
		    ::= { lte153Laser 35 }
		 
		unitStatusMajor       OBJECT-TYPE
		    SYNTAX            BITS 
		                      {
		                       systemTempHigh(0),
		                       systemTempLow(1),
		                       laserCurrentHigh(2),
		                       laserCurrentLow(3),
		                       laserTempHigh(4),
		                       laserTempLow(5),
		                       inputRFHigh(6),
		                       inputRFLow(7),
		                       opticalPowerHigh(8),
		                       opticalPowerLow(9),
		                       tecCurrentHigh(10),
		                       agcUnlock(11),
		                       keyInOffPosition(12),
		                       remoteOffModeSet(13)
		                      }
		    UNITS             "no units"
		    MAX-ACCESS        read-only
		    STATUS            current
		    DESCRIPTION       "Returns a bit mapped status word where each bit set (as defined below) 
		                       indicates a specific active alarm:
		
		                           0       1       2       3       4       5       6       7    
		                       +-------+-------+-------+-------+-------+-------+-------+-------+
		                       |System |System | Laser | Laser | Laser | Laser | Input | Input |
		                       | Temp  | Temp  |Current|Current| Temp  | Temp  |  RF   |  RF   |
		                       | High  | Low   | High  |  Low  | High  | Low   | Level | Level |
		                       |       |       |       |       |       |       |  High |  Low  |
		                       +-------+-------+-------+-------+-------+-------+-------+-------+
		
		                           8       9       10      11      12      13      14      15   
		                       +-------+-------+-------+-------+-------+-------+-------+-------+
		                       |Optical|Optical| TEC   |  AGC  |Key in |Remote |       |       |
		                       | Power | Power |Current| Unlock| Off   | Off   |       |       |
		                       |  Out  |  Out  | High  |       |Position Mode  |       |       |
		                       |       |       |       |       |       | Set   |       |       |
		                       +-------+-------+-------+-------+-------+-------+-------+-------+
		                      "
		    ::= { lte153Laser 36 }
		   
		unitStatusMinor       OBJECT-TYPE
		    SYNTAX            BITS 
		                      {
		                       systemTempHigh(0),
		                       systemTempLow(1),
		                       laserCurrentHigh(2),
		                       laserCurrentLow(3),
		                       laserTempHigh(4),
		                       laserTempLow(5),
		                       inputRFHigh(6),
		                       inputRFLow(7),
		                       opticalPowerHigh(8),
		                       opticalPowerLow(9),
		                       tecCurrentHigh(10),
		                       agcUnlock(11),
		                       keyInOffPosition(12),
		                       remoteOffModeSet(13)
		                      }
		    UNITS             "no units"
		    MAX-ACCESS        read-only
		    STATUS            current
		    DESCRIPTION       "Returns a bit mapped status word where each bit set (as defined below) 
		                       indicates a specific active warning:
		
		                           0       1       2       3       4       5       6       7    
		                       +-------+-------+-------+-------+-------+-------+-------+-------+
		                       |System |System | Laser | Laser | Laser | Laser | Input | Input |
		                       | Temp  | Temp  |Current|Current| Temp  | Temp  |  RF   |  RF   |
		                       | High  | Low   | High  |  Low  | High  | Low   | Level | Level |
		                       |       |       |       |       |       |       |  High |  Low  |
		                       +-------+-------+-------+-------+-------+-------+-------+-------+
		
		                           8       9       10      11      12      13      14      15   
		                       +-------+-------+-------+-------+-------+-------+-------+-------+
		                       |Optical|Optical| TEC   |  AGC  |Key in |Remote |       |       |
		                       | Power | Power |Current| Unlock| Off   | Off   |       |       |
		                       |  Out  |  Out  | High  |       |Position Mode  |       |       |
		                       |  High |  Low  |       |       |       | Set   |       |       |
		                       +-------+-------+-------+-------+-------+-------+-------+-------+
		                      "
		    ::= { lte153Laser 37 }
		    
		unitStatusHistory     OBJECT-TYPE
		    SYNTAX            BITS 
		                      {
		                       systemTempHigh(0),
		                       systemTempLow(1),
		                       laserCurrentHigh(2),
		                       laserCurrentLow(3),
		                       laserTempHigh(4),
		                       laserTempLow(5),
		                       inputRFHigh(6),
		                       inputRFLow(7),
		                       opticalPowerHigh(8),
		                       opticalPowerLow(9),
		                       tecCurrentHigh(10),
		                       agcUnlock(11),
		                       keyInOffPosition(12),
		                       remoteOffModeSet(13)
		                      }
		    UNITS             "no units"
		    MAX-ACCESS        read-write
		    STATUS            current
		    DESCRIPTION       "Returns a bit mapped status word where each bit set (as defined below) 
		                       indicates a an alarm had occurred since the last power up or clear:
		
		                           0       1       2       3       4       5       6       7    
		                       +-------+-------+-------+-------+-------+-------+-------+-------+
		                       |System |System | Laser | Laser | Laser | Laser | Input | Input |
		                       | Temp  | Temp  |Current|Current| Temp  | Temp  |  RF   |  RF   |
		                       | High  | Low   | High  |  Low  | High  | Low   | Level | Level |
		                       |       |       |       |       |       |       |  High |  Low  |
		                       +-------+-------+-------+-------+-------+-------+-------+-------+
		
		                           8       9       10      11      12      13      14      15   
		                       +-------+-------+-------+-------+-------+-------+-------+-------+
		                       |Optical|Optical| TEC   |  AGC  |Key in |Remote |       |       |
		                       | Power | Power |Current| Unlock| Off   | Off   |       |       |
		                       |  Out  |  Out  | High  |       |Position Mode  |       |       |
		                       |  High |  Low  |       |       |       | Set   |       |       |
		                       +-------+-------+-------+-------+-------+-------+-------+-------+
		
		                       Clear status history by writing a value of 0.
		                      "
		    ::= { lte153Laser 38 }
		  
		miscStatusEnable      OBJECT-TYPE
		    SYNTAX            BITS 
		                      {
		                       sbs2GHzPowerHigh(0),
		                       sbs2GHzPowerLow(1),
		                       sbs6GHzPowerHigh(2),
		                       sbs6GHzPowerLow(3),
		                       system5VPowerHigh(4),
		                       system5VPowerLow(5),
		                       system12VPowerHigh(6),
		                       system12VPowerLow(7),
		                       system24VPowerHigh(8),
		                       system24VPowerLow(9),
		                       systemM5VPowerHigh(10),
		                       systemM5VPowerLow(11),
		                       systemM12VPowerHigh(12),
		                       systemM12VPowerLow(13),
		                       communicationFailure(14),
		                       powerSupplyAFailure(16),
		                       powerSupplyBFailure(17),
		                       coolingFanAFailure(18),
		                       coolingFanBFailure(19)
		                      }
		    UNITS             "no units"
		    MAX-ACCESS        read-write
		    STATUS            current
		    DESCRIPTION       "Indicates the miscellaneous status alarm enable. This
		                       value is bit encoded therefore it is capable
		                       of indicating multiple alarm enable conditions. 
		                       The bits are defined as follows:
		
		                           0       1       2       3       4       5       6       7    
		                       +-------+-------+-------+-------+-------+-------+-------+-------+
		                       | 2 GHz | 2 GHz | 6 GHz | 6 GHz |System |System |System |System |
		                       | SBS   | SBS   | SBS   | SBS   | +5V   | +5V   | +12V  | +12V  |
		                       | Power | Power | Power | Power | Power | Power | Power | Power |
		                       | High  | Low   | High  | Low   | High  | Low   | High  | Low   |
		                       +-------+-------+-------+-------+-------+-------+-------+-------+
		
		                           8       9       10      11      12      13      14      15   
		                       +-------+-------+-------+-------+-------+-------+-------+-------+
		                       |System |System |System |System |System |System | Comm  |       |
		                       | +24V  | +24V  | -5V   | -5V   | -12V  | -12V  |Failure|       |
		                       | Power | Power | Power | Power | Power | Power |       |       |
		                       | High  | Low   | High  | Low   | High  | Low   |       |       |
		                       +-------+-------+-------+-------+-------+-------+-------+-------+
		
		                           16      17      18      19      20      21      22      23   
		                       +-------+-------+-------+-------+-------+-------+-------+-------+
		                       | Power | Power |Cooling|Cooling|       |       |       |       |
		                       | Supply| Supply|  Fan  |  Fan  |       |       |       |       |
		                       |   A   |   B   |   A   |   B   |       |       |       |       |
		                       |Failure|Failure|Failure|Failure|       |       |       |       |
		                       +-------+-------+-------+-------+-------+-------+-------+-------+
		                      "
		    ::= { lte153Laser 39 }
		 
		miscStatusMajor       OBJECT-TYPE
		    SYNTAX            BITS 
		                      {
		                       sbs2GHzPowerHigh(0),
		                       sbs2GHzPowerLow(1),
		                       sbs6GHzPowerHigh(2),
		                       sbs6GHzPowerLow(3),
		                       system5VPowerHigh(4),
		                       system5VPowerLow(5),
		                       system12VPowerHigh(6),
		                       system12VPowerLow(7),
		                       system24VPowerHigh(8),
		                       system24VPowerLow(9),
		                       systemM5VPowerHigh(10),
		                       systemM5VPowerLow(11),
		                       systemM12VPowerHigh(12),
		                       systemM12VPowerLow(13),
		                       communicationFailure(14),
		                       powerSupplyAFailure(16),
		                       powerSupplyBFailure(17),
		                       coolingFanAFailure(18),
		                       coolingFanBFailure(19)
		                      }
		    UNITS             "no units"
		    MAX-ACCESS        read-only
		    STATUS            current
		    DESCRIPTION       "Returns a bit mapped status word where each bit set (as defined below) 
		                       indicates a specific active alarm:
		
		                           0       1       2       3       4       5       6       7    
		                       +-------+-------+-------+-------+-------+-------+-------+-------+
		                       | 2 GHz | 2 GHz | 6 GHz | 6 GHz |System |System |System |System |
		                       | SBS   | SBS   | SBS   | SBS   | +5V   | +5V   | +12V  | +12V  |
		                       | Power | Power | Power | Power | Power | Power | Power | Power |
		                       | High  | Low   | High  | Low   | High  | Low   | High  | Low   |
		                       +-------+-------+-------+-------+-------+-------+-------+-------+
		
		                           8       9       10      11      12      13      14      15   
		                       +-------+-------+-------+-------+-------+-------+-------+-------+
		                       |System |System |System |System |System |System | Comm  |Power  |
		                       | +24V  | +24V  | -5V   | -5V   | -12V  | -12V  |Failure|Supply |
		                       | Power | Power | Power | Power | Power | Power |       |Failure|
		                       | High  | Low   | High  | Low   | High  | Low   |       |       |
		                       +-------+-------+-------+-------+-------+-------+-------+-------+
		
		                           16      17      18      19      20      21      22      23   
		                       +-------+-------+-------+-------+-------+-------+-------+-------+
		                       | Power | Power |Cooling|Cooling|       |       |       |       |
		                       | Supply| Supply|  Fan  |  Fan  |       |       |       |       |
		                       |   A   |   B   |   A   |   B   |       |       |       |       |
		                       |Failure|Failure|Failure|Failure|       |       |       |       |
		                       +-------+-------+-------+-------+-------+-------+-------+-------+
		                      "
		    ::= { lte153Laser 40 }
		   
		miscStatusMinor       OBJECT-TYPE
		    SYNTAX            BITS 
		                      {
		                       sbs2GHzPowerHigh(0),
		                       sbs2GHzPowerLow(1),
		                       sbs6GHzPowerHigh(2),
		                       sbs6GHzPowerLow(3),
		                       system5VPowerHigh(4),
		                       system5VPowerLow(5),
		                       system12VPowerHigh(6),
		                       system12VPowerLow(7),
		                       system24VPowerHigh(8),
		                       system24VPowerLow(9),
		                       systemM5VPowerHigh(10),
		                       systemM5VPowerLow(11),
		                       systemM12VPowerHigh(12),
		                       systemM12VPowerLow(13),
		                       communicationFailure(14),
		                       powerSupplyAFailure(16),
		                       powerSupplyBFailure(17),
		                       coolingFanAFailure(18),
		                       coolingFanBFailure(19)
		                      }
		    UNITS             "no units"
		    MAX-ACCESS        read-only
		    STATUS            current
		    DESCRIPTION       "Returns a bit mapped status word where each bit set (as defined below) 
		                       indicates a specific active warning:
		
		                           0       1       2       3       4       5       6       7    
		                       +-------+-------+-------+-------+-------+-------+-------+-------+
		                       | 2 GHz | 2 GHz | 6 GHz | 6 GHz |System |System |System |System |
		                       | SBS   | SBS   | SBS   | SBS   | +5V   | +5V   | +12V  | +12V  |
		                       | Power | Power | Power | Power | Power | Power | Power | Power |
		                       | High  | Low   | High  | Low   | High  | Low   | High  | Low   |
		                       +-------+-------+-------+-------+-------+-------+-------+-------+
		
		                           8       9       10      11      12      13      14      15   
		                       +-------+-------+-------+-------+-------+-------+-------+-------+
		                       |System |System |System |System |System |System | Comm  |Power  |
		                       | +24V  | +24V  | -5V   | -5V   | -12V  | -12V  |Failure|Supply |
		                       | Power | Power | Power | Power | Power | Power |       |Failure|
		                       | High  | Low   | High  | Low   | High  | Low   |       |       |
		                       +-------+-------+-------+-------+-------+-------+-------+-------+
		
		                           16      17      18      19      20      21      22      23   
		                       +-------+-------+-------+-------+-------+-------+-------+-------+
		                       | Power | Power |Cooling|Cooling|       |       |       |       |
		                       | Supply| Supply|  Fan  |  Fan  |       |       |       |       |
		                       |   A   |   B   |   A   |   B   |       |       |       |       |
		                       |Failure|Failure|Failure|Failure|       |       |       |       |
		                       +-------+-------+-------+-------+-------+-------+-------+-------+
		                      "
		    ::= { lte153Laser 41 }
		    
		miscStatusHistory     OBJECT-TYPE
		    SYNTAX            BITS 
		                      {
		                       sbs2GHzPowerHigh(0),
		                       sbs2GHzPowerLow(1),
		                       sbs6GHzPowerHigh(2),
		                       sbs6GHzPowerLow(3),
		                       system5VPowerHigh(4),
		                       system5VPowerLow(5),
		                       system12VPowerHigh(6),
		                       system12VPowerLow(7),
		                       system24VPowerHigh(8),
		                       system24VPowerLow(9),
		                       systemM5VPowerHigh(10),
		                       systemM5VPowerLow(11),
		                       systemM12VPowerHigh(12),
		                       systemM12VPowerLow(13),
		                       communicationFailure(14),
		                       powerSupplyAFailure(16),
		                       powerSupplyBFailure(17),
		                       coolingFanAFailure(18),
		                       coolingFanBFailure(19)
		                      }
		    UNITS             "no units"
		    MAX-ACCESS        read-write
		    STATUS            current
		    DESCRIPTION       "Returns a bit mapped status word where each bit set (as defined below) 
		                       indicates a an alarm had occurred since the last power up or clear:
		
		                           0       1       2       3       4       5       6       7    
		                       +-------+-------+-------+-------+-------+-------+-------+-------+
		                       | 2 GHz | 2 GHz | 6 GHz | 6 GHz |System |System |System |System |
		                       | SBS   | SBS   | SBS   | SBS   | +5V   | +5V   | +12V  | +12V  |
		                       | Power | Power | Power | Power | Power | Power | Power | Power |
		                       | High  | Low   | High  | Low   | High  | Low   | High  | Low   |
		                       +-------+-------+-------+-------+-------+-------+-------+-------+
		
		                           8       9       10      11      12      13      14      15   
		                       +-------+-------+-------+-------+-------+-------+-------+-------+
		                       |System |System |System |System |System |System | Comm  |Power  |
		                       | +24V  | +24V  | -5V   | -5V   | -12V  | -12V  |Failure|Supply |
		                       | Power | Power | Power | Power | Power | Power |       |Failure|
		                       | High  | Low   | High  | Low   | High  | Low   |       |       |
		                       +-------+-------+-------+-------+-------+-------+-------+-------+
		
		                           16      17      18      19      20      21      22      23   
		                       +-------+-------+-------+-------+-------+-------+-------+-------+
		                       | Power | Power |Cooling|Cooling|       |       |       |       |
		                       | Supply| Supply|  Fan  |  Fan  |       |       |       |       |
		                       |   A   |   B   |   A   |   B   |       |       |       |       |
		                       |Failure|Failure|Failure|Failure|       |       |       |       |
		                       +-------+-------+-------+-------+-------+-------+-------+-------+
		
		                       Clear status history by writing a value of 0.
		                      "
		    ::= { lte153Laser 42 }
		  
		frontPanelLEDStatus   OBJECT-TYPE
		    SYNTAX            BITS 
		                      {
		                       laserOn(0),
		                       laserOff(1),
		                       statusOkay(2),
		                       majorAlarmActive(3),
		                       minorAlarmActive(4),
		                       laserOnRearPanel(5)
		                      }
		    UNITS             "no units"
		    MAX-ACCESS        read-only
		    STATUS            current
		    DESCRIPTION       "Returns a bit mapped status word where each bit set (as defined below) 
		                       indicates a specific LED state:
		
		                           0       1       2       3       4       5
		                       +-------+-------+-------+-------+-------+-------+
		                       | Laser | Laser |Status |Status |Status |LaserOn|
		                       |  On   |  Off  | Okay  | Major | Minor | Rear  |
		                       |       |       |       | Alarm | Alarm | Panel |
		                       | Green |  Red  | Green |  Red  |  Red  | Green |
		                       +-------+-------+-------+-------+-------+-------+
		                      "
		    ::= { lte153Laser 43 }
		  
		upTime                OBJECT-TYPE
		    SYNTAX            TimeTicks
		    UNITS             "seconds"
		    MAX-ACCESS        read-only
		    STATUS            current
		    DESCRIPTION       "Returns the number of elapsed seconds since the last time the
		                       unit restarted." 
		    ::= { lte153Laser 44 }
		
		-----------------------------------------------------------------------
		-- BEGIN transmitter common events
		-----------------------------------------------------------------------
		transmitterNotificationPrefix    OBJECT IDENTIFIER ::= { lte153Laser 45 }
		transmitterCommonNotifications   OBJECT IDENTIFIER ::= { transmitterNotificationPrefix 0 }
		
		transmitterNoAlarmsPresent NOTIFICATION-TYPE
		--    OBJECTS      { }
		    STATUS       current
		    DESCRIPTION "No alarms are present."
		    ::= { transmitterCommonNotifications 0 }
		
		transmitterSystemTemperatureHigh NOTIFICATION-TYPE
		    OBJECTS      { unitStatus, systemTemp }
		    STATUS       current
		    DESCRIPTION "The system temperature has exceeded its normal operating value."
		    ::= { transmitterCommonNotifications 1 }
		
		transmitterSystemTemperatureLow NOTIFICATION-TYPE
		    OBJECTS      { unitStatus, systemTemp }
		    STATUS       current
		    DESCRIPTION "The system temperature has exceeded its normal operating value."
		    ::= { transmitterCommonNotifications 2 }
		
		transmitterLaserCurrentHigh NOTIFICATION-TYPE
		    OBJECTS      { unitStatus, laserCurrent }
		    STATUS       current
		    DESCRIPTION "The laser current has exceeded its normal operating value."
		    ::= { transmitterCommonNotifications 3 }
		
		transmitterLaserCurrentLow NOTIFICATION-TYPE
		    OBJECTS      { unitStatus, laserCurrent }
		    STATUS       current
		    DESCRIPTION "The laser current has exceeded its normal operating value."
		    ::= { transmitterCommonNotifications 4 }
		
		transmitterLaserTemperatureHigh NOTIFICATION-TYPE
		    OBJECTS      { unitStatus, laserTemperature }
		    STATUS       current
		    DESCRIPTION "The laser temperature has exceeded its normal operating value."
		    ::= { transmitterCommonNotifications 5 }
		
		transmitterLaserTemperatureLow NOTIFICATION-TYPE
		    OBJECTS      { unitStatus, LaserTemp }
		    STATUS       current
		    DESCRIPTION "The laser temperature has exceeded its normal operating value."
		    ::= { transmitterCommonNotifications 6 }
		
		transmitterInputRFLevelHigh NOTIFICATION-TYPE
		    OBJECTS      { unitStatus, inputRFLevel }
		    STATUS       current
		    DESCRIPTION "The input RF level has exceeded its normal operating value."
		    ::= { transmitterCommonNotifications 7 }
		
		transmitterInputRFLevelLow NOTIFICATION-TYPE
		    OBJECTS      { unitStatus, inputRFLevel }
		    STATUS       current
		    DESCRIPTION "The input RF level has exceeded its normal operating value."
		    ::= { transmitterCommonNotifications 8 }
		
		transmitterOpticalPowerOutputHigh NOTIFICATION-TYPE
		    OBJECTS      { unitStatus, opticalPowerOut1 }
		    STATUS       current
		    DESCRIPTION "The optical power output has exceeded its normal operating value."
		    ::= { transmitterCommonNotifications 9 }
		
		transmitterOpticalPowerOutputLow NOTIFICATION-TYPE
		    OBJECTS      { unitStatus, opticalPowerOut1 }
		    STATUS       current
		    DESCRIPTION "The optical power output has exceeded its normal operating value."
		    ::= { transmitterCommonNotifications 10 }
		
		transmitterTECCurrentHigh NOTIFICATION-TYPE
		    OBJECTS      { unitStatus, tecCurrent }
		    STATUS       current
		    DESCRIPTION "The thermoelectric cooler current has exceeded its normal operating value."
		    ::= { transmitterCommonNotifications 11 }
		
		transmitterAGCUnlocked NOTIFICATION-TYPE
		    OBJECTS      { unitStatus, compositeRFLevel }
		    STATUS       current
		    DESCRIPTION "The RF attenuator automatic gain control (AGC) is outside its normal operating range."
		    ::= { transmitterCommonNotifications 12 }
		
		transmitterKeySwitchOffPosition NOTIFICATION-TYPE
		    OBJECTS      { unitStatus, keyswitch }
		    STATUS       current
		    DESCRIPTION "The key switch is in the OFF position."
		    ::= { transmitterCommonNotifications 13 }
		
		transmitterRemoteLaserOffMode NOTIFICATION-TYPE
		    OBJECTS      { unitStatus, remoteControl }
		    STATUS       current
		    DESCRIPTION "The remote laser control is commanded to be in OFF mode."
		    ::= { transmitterCommonNotifications 14 }
		
		transmitter2GHzSBSPowerHigh NOTIFICATION-TYPE
		    OBJECTS      { miscStatus, sbs2GHzPower }
		    STATUS       current
		    DESCRIPTION "The 2GHz SBS output power has exceeded its normal operating value."
		    ::= { transmitterCommonNotifications 15 }
		
		transmitter2GHzSBSPowerLow NOTIFICATION-TYPE
		    OBJECTS      { miscStatus, sbs2GHzPower }
		    STATUS       current
		    DESCRIPTION "The 2GHz SBS output power has exceeded its normal operating value."
		    ::= { transmitterCommonNotifications 16 }
		
		transmitter6GHzSBSPowerHigh NOTIFICATION-TYPE
		    OBJECTS      { miscStatus, sbs6GHzPower }
		    STATUS       current
		    DESCRIPTION "The 6GHz SBS output power has exceeded its normal operating value."
		    ::= { transmitterCommonNotifications 17 }
		
		transmitter6GHzSBSPowerLow NOTIFICATION-TYPE
		    OBJECTS      { miscStatus, sbs6GHzPower }
		    STATUS       current
		    DESCRIPTION "The 6GHz SBS output power has exceeded its normal operating value."
		    ::= { transmitterCommonNotifications 18 }
		
		transmitterSystem5VPowerHigh NOTIFICATION-TYPE
		    OBJECTS      { miscStatus, monitor5v }
		    STATUS       current
		    DESCRIPTION "The system +5V power supply has exceeded its normal operating value."
		    ::= { transmitterCommonNotifications 19 }
		
		transmitterSystem5VPowerLow NOTIFICATION-TYPE
		    OBJECTS      { miscStatus, monitor5v }
		    STATUS       current
		    DESCRIPTION "The system +5V power supply has exceeded its normal operating value."
		    ::= { transmitterCommonNotifications 20 }
		
		transmitterSystem12VPowerHigh NOTIFICATION-TYPE
		    OBJECTS      { miscStatus, monitor12v }
		    STATUS       current
		    DESCRIPTION "The system +12V power supply has exceeded its normal operating value."
		    ::= { transmitterCommonNotifications 21 }
		
		transmitterSystem12VPowerLow NOTIFICATION-TYPE
		    OBJECTS      { miscStatus, monitor12v }
		    STATUS       current
		    DESCRIPTION "The system +12V power supply has exceeded its normal operating value."
		    ::= { transmitterCommonNotifications 22 }
		
		transmitterSystem24VPowerHigh NOTIFICATION-TYPE
		    OBJECTS      { miscStatus, monitor24v }
		    STATUS       current
		    DESCRIPTION "The system +24V power supply has exceeded its normal operating value."
		    ::= { transmitterCommonNotifications 23 }
		
		transmitterSystem24VPowerLow NOTIFICATION-TYPE
		    OBJECTS      { miscStatus, monitor24v }
		    STATUS       current
		    DESCRIPTION "The system +24V power supply has exceeded its normal operating value."
		    ::= { transmitterCommonNotifications 24 }
		
		transmitterSystemM5VPowerHigh NOTIFICATION-TYPE
		    OBJECTS      { miscStatus, monitorM5v }
		    STATUS       current
		    DESCRIPTION "The system -5V power supply has exceeded its normal operating value."
		    ::= { transmitterCommonNotifications 25 }
		
		transmitterSystemM5VPowerLow NOTIFICATION-TYPE
		    OBJECTS      { miscStatus, monitorM5v }
		    STATUS       current
		    DESCRIPTION "The system -5V power supply has exceeded its normal operating value."
		    ::= { transmitterCommonNotifications 26 }
		
		transmitterSystemM12VPowerHigh NOTIFICATION-TYPE
		    OBJECTS      { miscStatus, monitorM12v }
		    STATUS       current
		    DESCRIPTION "The system -12V power supply has exceeded its normal operating value."
		    ::= { transmitterCommonNotifications 27 }
		
		transmitterSystemM12VPowerLow NOTIFICATION-TYPE
		    OBJECTS      { miscStatus, monitorM12v }
		    STATUS       current
		    DESCRIPTION "The system -12V power supply has exceeded its normal operating value."
		    ::= { transmitterCommonNotifications 28 }
		
		transmitterCommunicationFailure NOTIFICATION-TYPE
		    OBJECTS      { miscStatus }
		    STATUS       current
		    DESCRIPTION "A failure was detected with the internal network communication interface."
		    ::= { transmitterCommonNotifications 29 }
		
		transmitterPowerSupplyAFailure NOTIFICATION-TYPE
		    OBJECTS      { miscStatus }
		    STATUS       current
		    DESCRIPTION "A failure was detected with power supply module A."
		    ::= { transmitterCommonNotifications 30 }
		
		transmitterPowerSupplyBFailure NOTIFICATION-TYPE
		    OBJECTS      { miscStatus }
		    STATUS       current
		    DESCRIPTION "A failure was detected with power supply module B."
		    ::= { transmitterCommonNotifications 31 }
		
		transmitterCoolingFanAFailure NOTIFICATION-TYPE
		    OBJECTS      { miscStatus }
		    STATUS       current
		    DESCRIPTION "A failure was detected with cooling fan A."
		    ::= { transmitterCommonNotifications 32 }
		
		transmitterCoolingFanBFailure NOTIFICATION-TYPE
		    OBJECTS      { miscStatus }
		    STATUS       current
		    DESCRIPTION "A failure was detected with cooling fan B."
		    ::= { transmitterCommonNotifications 33 }
		
		-----------------------------------------------------------------------
		-- END transmitter common events
		-----------------------------------------------------------------------
		
		
-- Product Information Tree
		-- 1.3.6.1.4.1.11606.7.2
		lte153PowerSupply OBJECT IDENTIFIER ::= { lte153 2 }              

        powerSupplyType       OBJECT-TYPE
   			SYNTAX            INTEGER { undefined(0),single5V(1),dualRedundant5V(2),single5-12-24V(3),dualRedundant5-12-24V(4) }
    		UNITS             "no units"
    		MAX-ACCESS        read-only
    		STATUS            current
    		DESCRIPTION       "Returns the installed power supply type.
                       
                       single5V(1)              - Single AC/DC power supply with rated output of 5V at 100W.
                       dualRedundant5V(2)       - Dual, redundant AC/DC power supplies with rated output of 
                                                     5V at 100W each.
                       single5-12-24V(3)        - Single AC/DC power supply with rated outputs of 5V, +/-12V
                                                     and 24V at 100W total.
                       dualRedundant5-12-24V(4) - Dual, redundant AC/DC power supplies with rated outputs of
                                                     5V, +/-12V and 24V at 100W total.
                      " 
   			::= { lte153PowerSupply 1 }
 
		powerSupplyTemp       OBJECT-TYPE
    		SYNTAX            Integer32(-500..1200)
    		UNITS             "tenth of a Celsius degree(C)"
		    MAX-ACCESS        read-only
		    STATUS            current
		    DESCRIPTION       "Returns the power supply regulator temperature."
		    ::= { lte153PowerSupply 2 }

		powerSupplyStatusA    OBJECT-TYPE
		    SYNTAX            INTEGER { undefined(0),nominal(1),failure(2),notInstalled(3) }
		    UNITS             "no units"
		    MAX-ACCESS        read-only
		    STATUS            current
		    DESCRIPTION       "Returns the operating status of power supply A."
		    ::= { lte153PowerSupply 3 }

		powerSupplyStatusB    OBJECT-TYPE
		    SYNTAX            INTEGER { undefined(0),nominal(1),failure(2),notInstalled(3) }
		    UNITS             "no units"
		    MAX-ACCESS        read-only
		    STATUS            current
		    DESCRIPTION       "Returns the operating status of power supply B."
		    ::= { lte153PowerSupply 4 }
	
		coolingFanA           OBJECT-TYPE
		    SYNTAX            INTEGER { undefined(0),nominal(1),failure(2),notInstalled(3) }
		    UNITS             "no units"
		    MAX-ACCESS        read-only
		    STATUS            current
		    DESCRIPTION       "Returns the operating status of chassis cooling fan A."
		    ::= { lte153PowerSupply 5 }
	
		coolingFanB           OBJECT-TYPE
		    SYNTAX            INTEGER { undefined(0),nominal(1),failure(2),notInstalled(3) }
		    UNITS             "no units"
		    MAX-ACCESS        read-only
		    STATUS            current
		    DESCRIPTION       "Returns the operating status of chassis cooling fan B."
		    ::= { lte153PowerSupply 6 }
	
		-----------------------------------------------------------------------
		-- BEGIN power supply events
		-----------------------------------------------------------------------
		powerSupplyNotificationPrefix    OBJECT IDENTIFIER ::= { lte153PowerSupply 8 }
		powerSupplyNotifications   OBJECT IDENTIFIER ::= { powerSupplyNotificationPrefix 0 }
		
		powerSupplyNoAlarmsPresent NOTIFICATION-TYPE
		--    OBJECTS      { }
		    STATUS       current
		    DESCRIPTION  "No alarms are present."
		    ::= { powerSupplyNotifications 0 }
		
		powerSupplyPowerSupplyFailureA NOTIFICATION-TYPE
		    OBJECTS      { powerSupplyStatusA }
		    STATUS       current
		    DESCRIPTION  "A failure was detected with power supply module A."
		    ::= { powerSupplyNotifications 1 }
		
		powerSupplyPowerSupplyFailureB NOTIFICATION-TYPE
		    OBJECTS      { powerSupplyStatusB }
		    STATUS       current
		    DESCRIPTION  "A failure was detected with power supply module B."
		    ::= { powerSupplyNotifications 2 }
		
		powerSupplyCoolingFanFailureA NOTIFICATION-TYPE
		    OBJECTS      { coolingFanStatusA }
		    STATUS       current
		    DESCRIPTION  "A failure was detected with chassis cooling fan A."
		    ::= { powerSupplyNotifications 3 }
		
		powerSupplyCoolingFanFailureB NOTIFICATION-TYPE
		    OBJECTS      { coolingFanStatusB }
		    STATUS       current
		    DESCRIPTION  "A failure was detected with chassis cooling fan B."
		    ::= { powerSupplyNotifications 4 }
		
		-----------------------------------------------------------------------
		-- END power supply events
		-----------------------------------------------------------------------
	
	
	
	
--
-- Trap definitions
--
	
-- **************************************************************************
-- ***************** TRAP FOR OCMF, OCMR, OCMC ******************************
-- **************************************************************************
-- **************************************************************************
-- pbnTrap : The PBN enterprise trap URGENT Alarm
		module15 TRAP-TYPE 
			ENTERPRISE pbnTrap
			VARIABLES { ocmSlot, ocmParam, ocmParamString, ocmParamStatus }
			DESCRIPTION 
				"PBN Module 1 Param 5 Alarm notification"
			::=  15

-- **************************************************************************
-- pbnTrap : The PBN enterprise trap NONURGENT Alarm
		module16 TRAP-TYPE 
			ENTERPRISE pbnTrap
			VARIABLES { ocmSlot, ocmParam, ocmParamString, ocmParamStatus }
			DESCRIPTION 
				"PBN Module 1 Param 6 Alarm notification"
			::=  16

-- **************************************************************************
-- pbnTrap : The PBN enterprise trap NONURGENT Alarm
		module17 TRAP-TYPE 
			ENTERPRISE pbnTrap
			VARIABLES { ocmSlot, ocmParam, ocmParamString, ocmParamStatus }
			DESCRIPTION 
				"PBN Module 1 Param 7 Alarm notification"
			::=  17

-- **************************************************************************
-- pbnTrap : The PBN enterprise trap NONURGENT Alarm
		module18 TRAP-TYPE 
			ENTERPRISE pbnTrap
			VARIABLES { ocmSlot, ocmParam, ocmParamString, ocmParamStatus }
			DESCRIPTION 
				"PBN Module 1 Param 8 Alarm notification"
			::=  18

-- **************************************************************************
-- pbnTrap : The PBN enterprise trap NONURGENT Alarm
		module19 TRAP-TYPE 
			ENTERPRISE pbnTrap
			VARIABLES { ocmSlot, ocmParam, ocmParamString, ocmParamStatus }
			DESCRIPTION 
				"PBN Module 1 Param 9 notification"
			::=  19

-- **************************************************************************
-- pbnTrap : The PBN enterprise trap NONURGENT Alarm
		module25 TRAP-TYPE 
			ENTERPRISE pbnTrap
			VARIABLES { ocmSlot, ocmParam, ocmParamString, ocmParamStatus }
			DESCRIPTION 
				"PBN Module 2 Param 5 notification"
			::=  25

-- **************************************************************************
-- pbnTrap : The PBN enterprise trap NONURGENT Alarm
		module26 TRAP-TYPE 
			ENTERPRISE pbnTrap
			VARIABLES { ocmSlot, ocmParam, ocmParamString, ocmParamStatus }
			DESCRIPTION 
				"PBN Module 2 Param 6 notification"
			::=  26

-- **************************************************************************
-- pbnTrap : The PBN enterprise trap NONURGENT Alarm
		module27 TRAP-TYPE 
			ENTERPRISE pbnTrap
			VARIABLES { ocmSlot, ocmParam, ocmParamString, ocmParamStatus }
			DESCRIPTION 
				"PBN Module 2 Param 7 notification"
			::=  27

-- **************************************************************************
-- pbnTrap : The PBN enterprise trap URGENT Alarm
		module28 TRAP-TYPE 
			ENTERPRISE pbnTrap
			VARIABLES { ocmSlot, ocmParam, ocmParamString, ocmParamStatus }
			DESCRIPTION 
				"PBN Module 2 Param 8 notification"
			::=  28

-- **************************************************************************
-- pbnTrap : The PBN enterprise trap NONURGENT Alarm
		module29 TRAP-TYPE 
			ENTERPRISE pbnTrap
			VARIABLES { ocmSlot, ocmParam, ocmParamString, ocmParamStatus }
			DESCRIPTION 
				"PBN Module 2 Param 9 notification"
			::=  29

-- **************************************************************************
-- pbnTrap : The PBN enterprise trap NONURGENT Alarm
		module35 TRAP-TYPE 
			ENTERPRISE pbnTrap
			VARIABLES { ocmSlot, ocmParam, ocmParamString, ocmParamStatus }
			DESCRIPTION 
				"PBN Module 3 Param 5 notification"
			::=  35

-- **************************************************************************
-- pbnTrap : The PBN enterprise trap NONURGENT Alarm
		module36 TRAP-TYPE 
			ENTERPRISE pbnTrap
			VARIABLES { ocmSlot, ocmParam, ocmParamString, ocmParamStatus }
			DESCRIPTION 
				"PBN Module 3 Param 6 notification"
			::=  36

-- **************************************************************************
-- pbnTrap : The PBN enterprise trap NONURGENT Alarm
		module37 TRAP-TYPE 
			ENTERPRISE pbnTrap
			VARIABLES { ocmSlot, ocmParam, ocmParamString, ocmParamStatus }
			DESCRIPTION 
				"PBN Module 3 Param 7 notification"
			::=  37

-- **************************************************************************
-- pbnTrap : The PBN enterprise trap NONURGENT Alarm
		module38 TRAP-TYPE 
			ENTERPRISE pbnTrap
			VARIABLES { ocmSlot, ocmParam, ocmParamString, ocmParamStatus }
			DESCRIPTION 
				"PBN Module 3 Param 8 notification"
			::=  38

-- **************************************************************************
-- pbnTrap : The PBN enterprise trap NONURGENT Alarm
		module39 TRAP-TYPE 
			ENTERPRISE pbnTrap
			VARIABLES { ocmSlot, ocmParam, ocmParamString, ocmParamStatus }
			DESCRIPTION 
				"PBN Module 3 Param 9 notification"
			::=  39

-- **************************************************************************
-- pbnTrap : The PBN enterprise trap NONURGENT Alarm
		module45 TRAP-TYPE 
			ENTERPRISE pbnTrap
			VARIABLES { ocmSlot, ocmParam, ocmParamString, ocmParamStatus }
			DESCRIPTION 
				"PBN Module 4 Param 5 notification"
			::=  45

-- **************************************************************************
-- pbnTrap : The PBN enterprise trap NONURGENT Alarm
		module46 TRAP-TYPE 
			ENTERPRISE pbnTrap
			VARIABLES { ocmSlot, ocmParam, ocmParamString, ocmParamStatus }
			DESCRIPTION 
				"PBN Module 4 Param 6 notification"
			::=  46

-- **************************************************************************
-- pbnTrap : The PBN enterprise trap NONURGENT Alarm
		module47 TRAP-TYPE 
			ENTERPRISE pbnTrap
			VARIABLES { ocmSlot, ocmParam, ocmParamString, ocmParamStatus }
			DESCRIPTION 
				"PBN Module 4 Param 7 notification"
			::=  47

-- **************************************************************************
-- pbnTrap : The PBN enterprise trap NONURGENT Alarm
		module48 TRAP-TYPE 
			ENTERPRISE pbnTrap
			VARIABLES { ocmSlot, ocmParam, ocmParamString, ocmParamStatus }
			DESCRIPTION 
				"PBN Module 4 Param 8 notification"
			::=  48

-- **************************************************************************
-- pbnTrap : The PBN enterprise trap NONURGENT Alarm
		module49 TRAP-TYPE 
			ENTERPRISE pbnTrap
			VARIABLES { ocmSlot, ocmParam, ocmParamString, ocmParamStatus }
			DESCRIPTION 
				"PBN Module 4 Param 9 notification"
			::=  49

-- **************************************************************************
-- pbnTrap : The PBN enterprise trap NONURGENT Alarm
		module110 TRAP-TYPE 
			ENTERPRISE pbnTrap
			VARIABLES { ocmSlot, ocmParam, ocmParamString, ocmParamStatus }
			DESCRIPTION 
				"PBN Module 1 Param 10 notification"
			::=  110

-- **************************************************************************
-- pbnTrap : The PBN enterprise trap NONURGENT Alarm
		module111 TRAP-TYPE 
			ENTERPRISE pbnTrap
			VARIABLES { ocmSlot, ocmParam, ocmParamString, ocmParamStatus }
			DESCRIPTION 
				"PBN Module 1 Param 11 notification"
			::=  111

-- **************************************************************************
-- pbnTrap : The PBN enterprise trap NONURGENT Alarm
		module112 TRAP-TYPE 
			ENTERPRISE pbnTrap
			VARIABLES { ocmSlot, ocmParam, ocmParamString, ocmParamStatus }
			DESCRIPTION 
				"PBN Module 1 Param 12 notification"
			::=  112

-- **************************************************************************
-- pbnTrap : The PBN enterprise trap NONURGENT Alarm
		module113 TRAP-TYPE 
			ENTERPRISE pbnTrap
			VARIABLES { ocmSlot, ocmParam, ocmParamString, ocmParamStatus }
			DESCRIPTION 
				"PBN Module 1 Param 13 notification"
			::=  113

-- **************************************************************************
-- pbnTrap : The PBN enterprise trap NONURGENT Alarm
		module114 TRAP-TYPE 
			ENTERPRISE pbnTrap
			VARIABLES { ocmSlot, ocmParam, ocmParamString, ocmParamStatus }
			DESCRIPTION 
				"PBN Module 1 Param 14 notification"
			::=  114

-- **************************************************************************
-- pbnTrap : The PBN enterprise trap URGENT Alarm
		module115 TRAP-TYPE 
			ENTERPRISE pbnTrap
			VARIABLES { ocmSlot, ocmParam, ocmParamString, ocmParamStatus }
			DESCRIPTION 
				"PBN Module 1 Param 15 notification"
			::=  115

-- **************************************************************************
-- pbnTrap : The PBN enterprise trap NONURGENT Alarm
		module116 TRAP-TYPE 
			ENTERPRISE pbnTrap
			VARIABLES { ocmSlot, ocmParam, ocmParamString, ocmParamStatus }
			DESCRIPTION 
				"PBN Module 1 Param 16 notification"
			::=  116

-- **************************************************************************
-- pbnTrap : The PBN enterprise trap NONURGENT Alarm
		module117 TRAP-TYPE 
			ENTERPRISE pbnTrap
			VARIABLES { ocmSlot, ocmParam, ocmParamString, ocmParamStatus }
			DESCRIPTION 
				"PBN Module 1 Param 17 notification"
			::=  117

-- **************************************************************************
-- pbnTrap : The PBN enterprise trap NONURGENT Alarm
		module118 TRAP-TYPE 
			ENTERPRISE pbnTrap
			VARIABLES { ocmSlot, ocmParam, ocmParamString, ocmParamStatus }
			DESCRIPTION 
				"PBN Module 1 Param 18 notification"
			::=  118

-- **************************************************************************
-- pbnTrap : The PBN enterprise trap NONURGENT Alarm
		module119 TRAP-TYPE 
			ENTERPRISE pbnTrap
			VARIABLES { ocmSlot, ocmParam, ocmParamString, ocmParamStatus }
			DESCRIPTION 
				"PBN Module 1 Param 19 notification"
			::=  119

-- **************************************************************************
-- pbnTrap : The PBN enterprise trap NONURGENT Alarm
		module120 TRAP-TYPE 
			ENTERPRISE pbnTrap
			VARIABLES { ocmSlot, ocmParam, ocmParamString, ocmParamStatus }
			DESCRIPTION 
				"PBN Module 1 Param 20 notification"
			::=  120

-- **************************************************************************
-- pbnTrap : The PBN enterprise trap NONURGENT Alarm
		module121 TRAP-TYPE 
			ENTERPRISE pbnTrap
			VARIABLES { ocmSlot, ocmParam, ocmParamString, ocmParamStatus }
			DESCRIPTION 
				"PBN Module 1 Param 21 notification"
			::=  121

-- **************************************************************************
-- pbnTrap : The PBN enterprise trap NONURGENT Alarm
		module122 TRAP-TYPE 
			ENTERPRISE pbnTrap
			VARIABLES { ocmSlot, ocmParam, ocmParamString, ocmParamStatus }
			DESCRIPTION 
				"PBN Module 1 Param 22 notification"
			::=  122

-- **************************************************************************
-- pbnTrap : The PBN enterprise trap NONURGENT Alarm
		module123 TRAP-TYPE 
			ENTERPRISE pbnTrap
			VARIABLES { ocmSlot, ocmParam, ocmParamString, ocmParamStatus }
			DESCRIPTION 
				"PBN Module 1 Param 23 notification"
			::=  123

-- **************************************************************************
-- pbnTrap : The PBN enterprise trap NONURGENT Alarm
		module124 TRAP-TYPE 
			ENTERPRISE pbnTrap
			VARIABLES { ocmSlot, ocmParam, ocmParamString, ocmParamStatus }
			DESCRIPTION 
				"PBN Module 1 Param 24 notification"
			::=  124

-- **************************************************************************
-- pbnTrap : The PBN enterprise trap NONURGENT Alarm
		module125 TRAP-TYPE 
			ENTERPRISE pbnTrap
			VARIABLES { ocmSlot, ocmParam, ocmParamString, ocmParamStatus }
			DESCRIPTION 
				"PBN Module 1 Param 25 notification"
			::=  125

-- **************************************************************************
-- pbnTrap : The PBN enterprise trap NONURGENT Alarm
		module126 TRAP-TYPE 
			ENTERPRISE pbnTrap
			VARIABLES { ocmSlot, ocmParam, ocmParamString, ocmParamStatus }
			DESCRIPTION 
				"PBN Module 1 Param 26 notification"
			::=  126

-- **************************************************************************
-- pbnTrap : The PBN enterprise trap NONURGENT Alarm
		module127 TRAP-TYPE 
			ENTERPRISE pbnTrap
			VARIABLES { ocmSlot, ocmParam, ocmParamString, ocmParamStatus }
			DESCRIPTION 
				"PBN Module 1 Param 27 notification"
			::=  127

-- **************************************************************************
-- pbnTrap : The PBN enterprise trap NONURGENT Alarm
		module128 TRAP-TYPE 
			ENTERPRISE pbnTrap
			VARIABLES { ocmSlot, ocmParam, ocmParamString, ocmParamStatus }
			DESCRIPTION 
				"PBN Module 1 Param 28 notification"
			::=  128

-- **************************************************************************
-- pbnTrap : The PBN enterprise trap NONURGENT Alarm
		module129 TRAP-TYPE 
			ENTERPRISE pbnTrap
			VARIABLES { ocmSlot, ocmParam, ocmParamString, ocmParamStatus }
			DESCRIPTION 
				"PBN Module 1 Param 29 notification"
			::=  129

-- **************************************************************************
-- pbnTrap : The PBN enterprise trap NONURGENT Alarm
		module130 TRAP-TYPE 
			ENTERPRISE pbnTrap
			VARIABLES { ocmSlot, ocmParam, ocmParamString, ocmParamStatus }
			DESCRIPTION 
				"PBN Module 1 Param 30 notification"
			::=  130

-- **************************************************************************
-- pbnTrap : The PBN enterprise trap NONURGENT Alarm
		module131 TRAP-TYPE 
			ENTERPRISE pbnTrap
			VARIABLES { ocmSlot, ocmParam, ocmParamString, ocmParamStatus }
			DESCRIPTION 
				"PBN Module 1 Param 31 notification"
			::=  131

-- **************************************************************************
-- pbnTrap : The PBN enterprise trap NONURGENT Alarm
		module210 TRAP-TYPE 
			ENTERPRISE pbnTrap
			VARIABLES { ocmSlot, ocmParam, ocmParamString, ocmParamStatus }
			DESCRIPTION 
				"PBN Module 2 Param 10 notification"
			::=  210

-- **************************************************************************
-- pbnTrap : The PBN enterprise trap NONURGENT Alarm
		module211 TRAP-TYPE 
			ENTERPRISE pbnTrap
			VARIABLES { ocmSlot, ocmParam, ocmParamString, ocmParamStatus }
			DESCRIPTION 
				"PBN Module 2 Param 11 notification"
			::=  211

-- **************************************************************************
-- pbnTrap : The PBN enterprise trap NONURGENT Alarm
		module212 TRAP-TYPE 
			ENTERPRISE pbnTrap
			VARIABLES { ocmSlot, ocmParam, ocmParamString, ocmParamStatus }
			DESCRIPTION 
				"PBN Module 2 Param 12 notification"
			::=  212

-- **************************************************************************
-- pbnTrap : The PBN enterprise trap NONURGENT Alarm
		module213 TRAP-TYPE 
			ENTERPRISE pbnTrap
			VARIABLES { ocmSlot, ocmParam, ocmParamString, ocmParamStatus }
			DESCRIPTION 
				"PBN Module 2 Param 13 notification"
			::=  213

-- **************************************************************************
-- pbnTrap : The PBN enterprise trap NONURGENT Alarm
		module214 TRAP-TYPE 
			ENTERPRISE pbnTrap
			VARIABLES { ocmSlot, ocmParam, ocmParamString, ocmParamStatus }
			DESCRIPTION 
				"PBN Module 2 Param 14 notification"
			::=  214

-- **************************************************************************
-- pbnTrap : The PBN enterprise trap NONURGENT Alarm
		module215 TRAP-TYPE 
			ENTERPRISE pbnTrap
			VARIABLES { ocmSlot, ocmParam, ocmParamString, ocmParamStatus }
			DESCRIPTION 
				"PBN Module 2 Param 15 notification"
			::=  215

-- **************************************************************************
-- pbnTrap : The PBN enterprise trap NONURGENT Alarm
		module216 TRAP-TYPE 
			ENTERPRISE pbnTrap
			VARIABLES { ocmSlot, ocmParam, ocmParamString, ocmParamStatus }
			DESCRIPTION 
				"PBN Module 2 Param 16 notification"
			::=  216

-- **************************************************************************
-- pbnTrap : The PBN enterprise trap NONURGENT Alarm
		module217 TRAP-TYPE 
			ENTERPRISE pbnTrap
			VARIABLES { ocmSlot, ocmParam, ocmParamString, ocmParamStatus }
			DESCRIPTION 
				"PBN Module 2 Param 17 notification"
			::=  217

-- **************************************************************************
-- pbnTrap : The PBN enterprise trap URGENT Alarm
		module218 TRAP-TYPE 
			ENTERPRISE pbnTrap
			VARIABLES { ocmSlot, ocmParam, ocmParamString, ocmParamStatus }
			DESCRIPTION 
				"PBN Module 2 Param 18 notification"
			::=  218

-- **************************************************************************
-- pbnTrap : The PBN enterprise trap NONURGENT Alarm
		module219 TRAP-TYPE 
			ENTERPRISE pbnTrap
			VARIABLES { ocmSlot, ocmParam, ocmParamString, ocmParamStatus }
			DESCRIPTION 
				"PBN Module 2 Param 19 Alarm notification"
			::=  219

-- **************************************************************************
-- pbnTrap : The PBN enterprise trap NONURGENT Alarm
		module220 TRAP-TYPE 
			ENTERPRISE pbnTrap
			VARIABLES { ocmSlot, ocmParam, ocmParamString, ocmParamStatus }
			DESCRIPTION 
				"PBN Module 2 Param 20 notification"
			::=  220

-- **************************************************************************
-- pbnTrap : The PBN enterprise trap NONURGENT Alarm
		module221 TRAP-TYPE 
			ENTERPRISE pbnTrap
			VARIABLES { ocmSlot, ocmParam, ocmParamString, ocmParamStatus }
			DESCRIPTION 
				"PBN Module 2 Param 21 notification"
			::=  221

-- **************************************************************************
-- pbnTrap : The PBN enterprise trap NONURGENT Alarm
		module222 TRAP-TYPE 
			ENTERPRISE pbnTrap
			VARIABLES { ocmSlot, ocmParam, ocmParamString, ocmParamStatus }
			DESCRIPTION 
				"PBN Module 2 Param 22 notification"
			::=  222

-- **************************************************************************
-- pbnTrap : The PBN enterprise trap NONURGENT Alarm
		module223 TRAP-TYPE 
			ENTERPRISE pbnTrap
			VARIABLES { ocmSlot, ocmParam, ocmParamString, ocmParamStatus }
			DESCRIPTION 
				"PBN Module 2 Param 23 notification"
			::=  223

-- **************************************************************************
-- pbnTrap : The PBN enterprise trap NONURGENT Alarm
		module224 TRAP-TYPE 
			ENTERPRISE pbnTrap
			VARIABLES { ocmSlot, ocmParam, ocmParamString, ocmParamStatus }
			DESCRIPTION 
				"PBN Module 2 Param 24 notification"
			::=  224

-- **************************************************************************
-- pbnTrap : The PBN enterprise trap NONURGENT Alarm
		module225 TRAP-TYPE 
			ENTERPRISE pbnTrap
			VARIABLES { ocmSlot, ocmParam, ocmParamString, ocmParamStatus }
			DESCRIPTION 
				"PBN Module 2 Param 25 notification"
			::=  225

-- **************************************************************************
-- pbnTrap : The PBN enterprise trap NONURGENT Alarm
		module226 TRAP-TYPE 
			ENTERPRISE pbnTrap
			VARIABLES { ocmSlot, ocmParam, ocmParamString, ocmParamStatus }
			DESCRIPTION 
				"PBN Module 2 Param 26 notification"
			::=  226

-- **************************************************************************
-- pbnTrap : The PBN enterprise trap NONURGENT Alarm
		module227 TRAP-TYPE 
			ENTERPRISE pbnTrap
			VARIABLES { ocmSlot, ocmParam, ocmParamString, ocmParamStatus }
			DESCRIPTION 
				"PBN Module 2 Param 27 notification"
			::=  227

-- **************************************************************************
-- pbnTrap : The PBN enterprise trap NONURGENT Alarm
		module228 TRAP-TYPE 
			ENTERPRISE pbnTrap
			VARIABLES { ocmSlot, ocmParam, ocmParamString, ocmParamStatus }
			DESCRIPTION 
				"PBN Module 2 Param 28 notification"
			::=  228

-- **************************************************************************
-- pbnTrap : The PBN enterprise trap NONURGENT Alarm
		module229 TRAP-TYPE 
			ENTERPRISE pbnTrap
			VARIABLES { ocmSlot, ocmParam, ocmParamString, ocmParamStatus }
			DESCRIPTION 
				"PBN Module 2 Param 29 notification"
			::=  229

-- **************************************************************************
-- pbnTrap : The PBN enterprise trap NONURGENT Alarm
		module230 TRAP-TYPE 
			ENTERPRISE pbnTrap
			VARIABLES { ocmSlot, ocmParam, ocmParamString, ocmParamStatus }
			DESCRIPTION 
				"PBN Module 2 Param 30 notification"
			::=  230

-- **************************************************************************
-- pbnTrap : The PBN enterprise trap NONURGENT Alarm
		module231 TRAP-TYPE 
			ENTERPRISE pbnTrap
			VARIABLES { ocmSlot, ocmParam, ocmParamString, ocmParamStatus }
			DESCRIPTION 
				"PBN Module 2 Param 31 notification"
			::=  231

-- **************************************************************************
-- pbnTrap : The PBN enterprise trap NONURGENT Alarm
		module310 TRAP-TYPE 
			ENTERPRISE pbnTrap
			VARIABLES { ocmSlot, ocmParam, ocmParamString, ocmParamStatus }
			DESCRIPTION 
				"PBN Module 3 Param 10 notification"
			::=  310

-- **************************************************************************
-- pbnTrap : The PBN enterprise trap URGENT Alarm
		module311 TRAP-TYPE 
			ENTERPRISE pbnTrap
			VARIABLES { ocmSlot, ocmParam, ocmParamString, ocmParamStatus }
			DESCRIPTION 
				"PBN Module 3 Param 11 notification"
			::=  311

-- **************************************************************************
-- pbnTrap : The PBN enterprise trap NONURGENT Alarm
		module312 TRAP-TYPE 
			ENTERPRISE pbnTrap
			VARIABLES { ocmSlot, ocmParam, ocmParamString, ocmParamStatus }
			DESCRIPTION 
				"PBN Module 3 Param 12 notification"
			::=  312

-- **************************************************************************
-- pbnTrap : The PBN enterprise trap NONURGENT Alarm
		module313 TRAP-TYPE 
			ENTERPRISE pbnTrap
			VARIABLES { ocmSlot, ocmParam, ocmParamString, ocmParamStatus }
			DESCRIPTION 
				"PBN Module 3 Param 13 notification"
			::=  313

-- **************************************************************************
-- pbnTrap : The PBN enterprise trap NONURGENT Alarm
		module314 TRAP-TYPE 
			ENTERPRISE pbnTrap
			VARIABLES { ocmSlot, ocmParam, ocmParamString, ocmParamStatus }
			DESCRIPTION 
				"PBN Module 3 Param 14 notification"
			::=  314

-- **************************************************************************
-- pbnTrap : The PBN enterprise trap NONURGENT Alarm
		module315 TRAP-TYPE 
			ENTERPRISE pbnTrap
			VARIABLES { ocmSlot, ocmParam, ocmParamString, ocmParamStatus }
			DESCRIPTION 
				"PBN Module 3 Param 15 notification"
			::=  315

-- **************************************************************************
-- pbnTrap : The PBN enterprise trap NONURGENT Alarm
		module316 TRAP-TYPE 
			ENTERPRISE pbnTrap
			VARIABLES { ocmSlot, ocmParam, ocmParamString, ocmParamStatus }
			DESCRIPTION 
				"PBN Module 3 Param 16 notification"
			::=  316

-- **************************************************************************
-- pbnTrap : The PBN enterprise trap NONURGENT Alarm
		module317 TRAP-TYPE 
			ENTERPRISE pbnTrap
			VARIABLES { ocmSlot, ocmParam, ocmParamString, ocmParamStatus }
			DESCRIPTION 
				"PBN Module 3 Param 17 notification"
			::=  317

-- **************************************************************************
-- pbnTrap : The PBN enterprise trap NONURGENT Alarm
		module318 TRAP-TYPE 
			ENTERPRISE pbnTrap
			VARIABLES { ocmSlot, ocmParam, ocmParamString, ocmParamStatus }
			DESCRIPTION 
				"PBN Module 3 Param 18 notification"
			::=  318

-- **************************************************************************
-- pbnTrap : The PBN enterprise trap NONURGENT Alarm
		module319 TRAP-TYPE 
			ENTERPRISE pbnTrap
			VARIABLES { ocmSlot, ocmParam, ocmParamString, ocmParamStatus }
			DESCRIPTION 
				"PBN Module 3 Param 19 notification"
			::=  319

-- **************************************************************************
-- pbnTrap : The PBN enterprise trap NONURGENT Alarm
		module320 TRAP-TYPE 
			ENTERPRISE pbnTrap
			VARIABLES { ocmSlot, ocmParam, ocmParamString, ocmParamStatus }
			DESCRIPTION 
				"PBN Module 3 Param 20 notification"
			::=  320

-- **************************************************************************
-- pbnTrap : The PBN enterprise trap URGENT Alarm
		module321 TRAP-TYPE 
			ENTERPRISE pbnTrap
			VARIABLES { ocmSlot, ocmParam, ocmParamString, ocmParamStatus }
			DESCRIPTION 
				"PBN Module 3 Param 21 notification"
			::=  321

-- **************************************************************************
-- pbnTrap : The PBN enterprise trap URGENT Alarm
		module322 TRAP-TYPE 
			ENTERPRISE pbnTrap
			VARIABLES { ocmSlot, ocmParam, ocmParamString, ocmParamStatus }
			DESCRIPTION 
				"PBN Module 3 Param 22 notification"
			::=  322

-- **************************************************************************
-- pbnTrap : The PBN enterprise trap URGENT Alarm
		module323 TRAP-TYPE 
			ENTERPRISE pbnTrap
			VARIABLES { ocmSlot, ocmParam, ocmParamString, ocmParamStatus }
			DESCRIPTION 
				"PBN Module 3 Param 23 notification"
			::=  323

-- **************************************************************************
-- pbnTrap : The PBN enterprise trap URGENT Alarm
		module324 TRAP-TYPE 
			ENTERPRISE pbnTrap
			VARIABLES { ocmSlot, ocmParam, ocmParamString, ocmParamStatus }
			DESCRIPTION 
				"PBN Module 3 Param 24 notification"
			::=  324

-- **************************************************************************
-- pbnTrap : The PBN enterprise trap URGENT Alarm
		module325 TRAP-TYPE 
			ENTERPRISE pbnTrap
			VARIABLES { ocmSlot, ocmParam, ocmParamString, ocmParamStatus }
			DESCRIPTION 
				"PBN Module 3 Param 25 notification"
			::=  325

-- **************************************************************************
-- pbnTrap : The PBN enterprise trap URGENT Alarm
		module326 TRAP-TYPE 
			ENTERPRISE pbnTrap
			VARIABLES { ocmSlot, ocmParam, ocmParamString, ocmParamStatus }
			DESCRIPTION 
				"PBN Module 3 Param 26 notification"
			::=  326

-- **************************************************************************
-- pbnTrap : The PBN enterprise trap URGENT Alarm
		module327 TRAP-TYPE 
			ENTERPRISE pbnTrap
			VARIABLES { ocmSlot, ocmParam, ocmParamString, ocmParamStatus }
			DESCRIPTION 
				"PBN Module 3 Param 27 notification"
			::=  327

-- **************************************************************************
-- pbnTrap : The PBN enterprise trap URGENT Alarm
		module328 TRAP-TYPE 
			ENTERPRISE pbnTrap
			VARIABLES { ocmSlot, ocmParam, ocmParamString, ocmParamStatus }
			DESCRIPTION 
				"PBN Module 3 Param 28 notification"
			::=  328

-- **************************************************************************
-- pbnTrap : The PBN enterprise trap URGENT Alarm
		module329 TRAP-TYPE 
			ENTERPRISE pbnTrap
			VARIABLES { ocmSlot, ocmParam, ocmParamString, ocmParamStatus }
			DESCRIPTION 
				"PBN Module 3 Param 29 notification"
			::=  329

-- **************************************************************************
-- pbnTrap : The PBN enterprise trap URGENT Alarm
		module330 TRAP-TYPE 
			ENTERPRISE pbnTrap
			VARIABLES { ocmSlot, ocmParam, ocmParamString, ocmParamStatus }
			DESCRIPTION 
				"PBN Module 3 Param 30 notification"
			::=  330

-- **************************************************************************
-- pbnTrap : The PBN enterprise trap URGENT Alarm
		module331 TRAP-TYPE 
			ENTERPRISE pbnTrap
			VARIABLES { ocmSlot, ocmParam, ocmParamString, ocmParamStatus }
			DESCRIPTION 
				"PBN Module 3 Param 31 notification"
			::=  331

-- **************************************************************************
-- pbnTrap : The PBN enterprise trap NONURGENT Alarm
		module410 TRAP-TYPE 
			ENTERPRISE pbnTrap
			VARIABLES { ocmSlot, ocmParam, ocmParamString, ocmParamStatus }
			DESCRIPTION 
				"PBN Module 4 Param 10 notification"
			::=  410

-- **************************************************************************
-- pbnTrap : The PBN enterprise trap NONURGENT Alarm
		module411 TRAP-TYPE 
			ENTERPRISE pbnTrap
			VARIABLES { ocmSlot, ocmParam, ocmParamString, ocmParamStatus }
			DESCRIPTION 
				"PBN Module 4 Param 11 notification"
			::=  411

-- **************************************************************************
-- CPON-100 Contact Input Trap
		cpon100ContactInput TRAP-TYPE 
			ENTERPRISE cpon100Trap
			VARIABLES { cpon100TrapMsg, cpon100MACAddr, cpon100TrapStatus, contactInput }
			DESCRIPTION 
				"CPON-100 Tamper alarm"
			::=  412

-- **************************************************************************
-- CPON-100 Sensing Input Trap
		cpon100sensingInput TRAP-TYPE 
			ENTERPRISE cpon100Trap
			VARIABLES { cpon100TrapMsg, cpon100MACAddr, cpon100TrapStatus, sensingInput }
			DESCRIPTION 
				"CPON-100 Battery alarm"
			::=  413

-- **************************************************************************
-- CPON-100 CATV Status Trap
		cpon100CATVAlarm TRAP-TYPE 
			ENTERPRISE cpon100Trap
			VARIABLES { catvStatus, cpon100TrapMsg, cpon100MACAddr, cpon100TrapStatus }
			DESCRIPTION 
				"CPON-100 CATV alarm"
			::=  414

		mauStatus5VTrap TRAP-TYPE 
			ENTERPRISE pbnTrap
			VARIABLES { mauProductMAC, mauTrapMessageDescr, mauStatus5V }
			::=  415

		mauStatus12VTrap TRAP-TYPE 
			ENTERPRISE pbnTrap
			VARIABLES { mauProductMAC, mauTrapMessageDescr, mauStatus12V }
			::=  416

		mauStatus24VTrap TRAP-TYPE 
			ENTERPRISE pbnTrap
			VARIABLES { mauProductMAC, mauTrapMessageDescr, mauStatus24V }
			::=  417

		mauStatusInputOpticalPowerTrap TRAP-TYPE 
			ENTERPRISE pbnTrap
			VARIABLES { mauProductMAC, mauTrapMessageDescr, mauStatusInputOpticalPower }
			::=  418

		mauStatusOutputOpticalPowerTrap TRAP-TYPE 
			ENTERPRISE pbnTrap
			VARIABLES { mauProductMAC, mauTrapMessageDescr, mauStatusOutputOpticalPower }
			::=  419

		mauStatusRFOutputTrap TRAP-TYPE 
			ENTERPRISE pbnTrap
			VARIABLES { mauProductMAC, mauTrapMessageDescr, mauStatusRFOutputPower }
			::=  420

		mauStatusTemperatureTrap TRAP-TYPE 
			ENTERPRISE pbnTrap
			VARIABLES { mauProductMAC, mauTrapMessageDescr, mauStatusTemperature }
			::=  421

		mauStatusLidTrap TRAP-TYPE 
			ENTERPRISE pbnTrap
			VARIABLES { mauProductMAC, mauTrapMessageDescr, mauStatusLid }
			::=  422

	
	END

--
-- PBN-MIB.mib
--
