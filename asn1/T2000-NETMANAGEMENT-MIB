--
-- T2000-NETMANAGEMENT-MIB.mib
-- MIB generated by MG-SOFT Visual MIB Builder Version 4.0 Build 349
-- Wednesday, September 28, 2005 at 11:43:28
--

	T2000-NETMANAGEMENT-MIB DEFINITIONS ::= BEGIN
 
		IMPORTS
			OBJECT-TYPE			
				FROM RFC-1212			
			TRAP-TYPE			
				FROM RFC-1215			
			enterprises, IpAddress			
				FROM RFC1155-SMI;
	
	
--
-- Node definitions
--
	
		-- 1.3.6.1.4.1.2011
		huawei OBJECT IDENTIFIER ::= { enterprises 2011 }

		
		-- 1.3.6.1.4.1.2011.2
		products OBJECT IDENTIFIER ::= { huawei 2 }

		
		-- 1.3.6.1.4.1.2011.2.15
		netManagement OBJECT IDENTIFIER ::= { products 15 }

		
		-- 1.3.6.1.4.1.2011.2.15.1
		nmAgent OBJECT IDENTIFIER ::= { netManagement 1 }

		
		-- 1.3.6.1.4.1.2011.2.15.1.7
		nmNorthboundEvent OBJECT IDENTIFIER ::= { nmAgent 7 }

		
		-- 1.3.6.1.4.1.2011.2.15.1.7.3
		northboundReportAlarm OBJECT IDENTIFIER ::= { nmNorthboundEvent 3 }

		
		-- 1.3.6.1.4.1.2011.2.15.1.7.3.1
		northboundReportAlarmManagedObjectClass OBJECT-TYPE
			SYNTAX OCTET STRING
			ACCESS read-only
			STATUS mandatory
			DESCRIPTION
				"DESCRIPTION"
			::= { northboundReportAlarm 1 }

		
		-- 1.3.6.1.4.1.2011.2.15.1.7.3.2
		northboundReportAlarmManagedObjectInstance OBJECT-TYPE
			SYNTAX OCTET STRING
			ACCESS read-only
			STATUS mandatory
			DESCRIPTION
				"DESCRIPTION"
			::= { northboundReportAlarm 2 }

		
		-- 1.3.6.1.4.1.2011.2.15.1.7.3.3
		northboundReportAlarmEventType OBJECT-TYPE
			SYNTAX OCTET STRING
			ACCESS read-only
			STATUS mandatory
			DESCRIPTION
				"DESCRIPTION"
			::= { northboundReportAlarm 3 }

		
		-- 1.3.6.1.4.1.2011.2.15.1.7.3.4
		northboundReportAlarmEventTime OBJECT-TYPE
			SYNTAX OCTET STRING
			ACCESS read-only
			STATUS mandatory
			DESCRIPTION
				"DESCRIPTION"
			::= { northboundReportAlarm 4 }

		
		-- 1.3.6.1.4.1.2011.2.15.1.7.3.5
		northboundReportAlarmProbableCause OBJECT-TYPE
			SYNTAX OCTET STRING
			ACCESS read-only
			STATUS mandatory
			DESCRIPTION
				"DESCRIPTION"
			::= { northboundReportAlarm 5 }

		
		-- 1.3.6.1.4.1.2011.2.15.1.7.3.6
		northboundReportAlarmSpecificProblems OBJECT-TYPE
			SYNTAX OCTET STRING
			ACCESS read-only
			STATUS mandatory
			DESCRIPTION
				"DESCRIPTION"
			::= { northboundReportAlarm 6 }

		
		-- 1.3.6.1.4.1.2011.2.15.1.7.3.7
		northboundReportAlarmPerceivedSeverity OBJECT-TYPE
			SYNTAX OCTET STRING
			ACCESS read-only
			STATUS mandatory
			DESCRIPTION
				"DESCRIPTION"
			::= { northboundReportAlarm 7 }

		
		-- 1.3.6.1.4.1.2011.2.15.1.7.3.8
		northboundReportAlarmNotificationIdentifier OBJECT-TYPE
			SYNTAX INTEGER
			ACCESS read-only
			STATUS mandatory
			DESCRIPTION
				"DESCRIPTION"
			DEFVAL { ''b }
			::= { northboundReportAlarm 8 }

		
		-- 1.3.6.1.4.1.2011.2.15.1.7.3.9
		northboundReportAlarmCorrelatedNotifications OBJECT-TYPE
			SYNTAX INTEGER
			ACCESS read-only
			STATUS mandatory
			DESCRIPTION
				"DESCRIPTION"
			DEFVAL { ''b }
			::= { northboundReportAlarm 9 }

		
		-- 1.3.6.1.4.1.2011.2.15.1.7.3.10
		northboundReportAlarmProposedRepairActions OBJECT-TYPE
			SYNTAX OCTET STRING
			ACCESS read-only
			STATUS mandatory
			DESCRIPTION
				"DESCRIPTION"
			::= { northboundReportAlarm 10 }

		
		-- 1.3.6.1.4.1.2011.2.15.1.7.3.11
		northboundReportAlarmAdditionalText OBJECT-TYPE
			SYNTAX OCTET STRING
			ACCESS read-only
			STATUS mandatory
			DESCRIPTION
				"DESCRIPTION"
			::= { northboundReportAlarm 11 }

		
		-- 1.3.6.1.4.1.2011.2.15.1.7.3.12
		northboundReportAlarmEmsName OBJECT-TYPE
			SYNTAX OCTET STRING
			ACCESS read-only
			STATUS mandatory
			DESCRIPTION
				"DESCRIPTION"
			::= { northboundReportAlarm 12 }

		
		-- 1.3.6.1.4.1.2011.2.15.1.7.3.13
		northboundReportAlarmNEName OBJECT-TYPE
			SYNTAX OCTET STRING
			ACCESS read-only
			STATUS mandatory
			DESCRIPTION
				"DESCRIPTION"
			::= { northboundReportAlarm 13 }

		
		-- 1.3.6.1.4.1.2011.2.15.1.7.3.14
		northboundReportAlarmDevLocation OBJECT-TYPE
			SYNTAX OCTET STRING
			ACCESS read-only
			STATUS mandatory
			DESCRIPTION
				"DESCRIPTION"
			::= { northboundReportAlarm 14 }

		
		-- 1.3.6.1.4.1.2011.2.15.1.7.3.15
		northboundReportAlarmRackName OBJECT-TYPE
			SYNTAX OCTET STRING
			ACCESS read-only
			STATUS mandatory
			DESCRIPTION
				"DESCRIPTION"
			::= { northboundReportAlarm 15 }

		
		-- 1.3.6.1.4.1.2011.2.15.1.7.3.16
		northboundReportAlarmShelfName OBJECT-TYPE
			SYNTAX OCTET STRING
			ACCESS read-only
			STATUS mandatory
			DESCRIPTION
				"DESCRIPTION"
			::= { northboundReportAlarm 16 }

		
		-- 1.3.6.1.4.1.2011.2.15.1.7.3.17
		northboundReportAlarmBoardName OBJECT-TYPE
			SYNTAX OCTET STRING
			ACCESS read-only
			STATUS mandatory
			DESCRIPTION
				"DESCRIPTION"
			::= { northboundReportAlarm 17 }

		
		-- 1.3.6.1.4.1.2011.2.15.1.7.3.18
		northboundReportAlarmPortType OBJECT-TYPE
			SYNTAX OCTET STRING
			ACCESS read-only
			STATUS mandatory
			DESCRIPTION
				"DESCRIPTION"
			::= { northboundReportAlarm 18 }

		
		-- 1.3.6.1.4.1.2011.2.15.1.7.3.19
		northboundReportAlarmPortNumber OBJECT-TYPE
			SYNTAX INTEGER
			ACCESS read-only
			STATUS mandatory
			DESCRIPTION
				"DESCRIPTION"
			DEFVAL { ''b }
			::= { northboundReportAlarm 19 }

		
		-- 1.3.6.1.4.1.2011.2.15.1.7.3.20
		northboundReportAlarmLocation OBJECT-TYPE
			SYNTAX OCTET STRING
			ACCESS read-only
			STATUS mandatory
			DESCRIPTION
				"DESCRIPTION"
			::= { northboundReportAlarm 20 }

		
		-- 1.3.6.1.4.1.2011.2.15.1.7.3.21
		northboundReportAlarmOperationAffected OBJECT-TYPE
			SYNTAX OCTET STRING
			ACCESS read-only
			STATUS mandatory
			DESCRIPTION
				"DESCRIPTION"
			::= { northboundReportAlarm 21 }

		
		-- 1.3.6.1.4.1.2011.2.15.1.7.3.22
		northboundReportAlarmID OBJECT-TYPE
			SYNTAX INTEGER
			ACCESS read-only
			STATUS mandatory
			DESCRIPTION
				"DESCRIPTION"
			DEFVAL { ''b }
			::= { northboundReportAlarm 22 }

		
		-- 1.3.6.1.4.1.2011.2.15.1.7.3.23
		northboundReportAlarmName OBJECT-TYPE
			SYNTAX OCTET STRING
			ACCESS read-only
			STATUS mandatory
			DESCRIPTION
				"DESCRIPTION"
			::= { northboundReportAlarm 23 }

		
		-- 1.3.6.1.4.1.2011.2.15.1.7.3.24
		northboundReportAlarmIPAddress OBJECT-TYPE
			SYNTAX IpAddress
			ACCESS read-only
			STATUS mandatory
			DESCRIPTION
				"DESCRIPTION"
			::= { northboundReportAlarm 24 }

		
		-- 1.3.6.1.4.1.2011.2.15.1.7.3.25
		northboundReportAlarmResourceID OBJECT-TYPE
			SYNTAX INTEGER
			ACCESS read-only
			STATUS mandatory
			DESCRIPTION
				"DESCRIPTION"
			DEFVAL { ''b }
			::= { northboundReportAlarm 25 }

		
		-- 1.3.6.1.4.1.2011.2.15.1.7.3.26
		northboundReportAlarmCleared OBJECT-TYPE
			SYNTAX INTEGER
			ACCESS read-only
			STATUS mandatory
			DESCRIPTION
				"DESCRIPTION"
			DEFVAL { ''b }
			::= { northboundReportAlarm 26 }

		
		-- 1.3.6.1.4.1.2011.2.15.1.7.3.27
		northboundReportAlarmAdditionalVB1 OBJECT-TYPE
			SYNTAX OCTET STRING
			ACCESS read-only
			STATUS mandatory
			DESCRIPTION
				"DESCRIPTION"
			::= { northboundReportAlarm 27 }

		
		-- 1.3.6.1.4.1.2011.2.15.1.7.3.28
		northboundReportAlarmAdditionalVB2 OBJECT-TYPE
			SYNTAX OCTET STRING
			ACCESS read-only
			STATUS mandatory
			DESCRIPTION
				"DESCRIPTION"
			::= { northboundReportAlarm 28 }

		
		-- 1.3.6.1.4.1.2011.2.15.1.7.3.29
		northboundReportAlarmAdditionalVB3 OBJECT-TYPE
			SYNTAX OCTET STRING
			ACCESS read-only
			STATUS mandatory
			DESCRIPTION
				"DESCRIPTION"
			::= { northboundReportAlarm 29 }

		
		-- 1.3.6.1.4.1.2011.2.15.1.7.3.30
		northboundReportAlarmAdditionalVB4 OBJECT-TYPE
			SYNTAX OCTET STRING
			ACCESS read-only
			STATUS mandatory
			DESCRIPTION
				"DESCRIPTION"
			::= { northboundReportAlarm 30 }

		
		-- 1.3.6.1.4.1.2011.2.15.1.7.3.31
		northboundReportAlarmAdditionalVB5 OBJECT-TYPE
			SYNTAX OCTET STRING
			ACCESS read-only
			STATUS mandatory
			DESCRIPTION
				"DESCRIPTION"
			::= { northboundReportAlarm 31 }

		
		-- 1.3.6.1.4.1.2011.2.15.1.7.3.32
		northboundReportAlarmAdditionalVB6 OBJECT-TYPE
			SYNTAX OCTET STRING
			ACCESS read-only
			STATUS mandatory
			DESCRIPTION
				"DESCRIPTION"
			::= { northboundReportAlarm 32 }

		
		-- 1.3.6.1.4.1.2011.2.15.1.7.3.33
		northboundReportAlarmAdditionalVB7 OBJECT-TYPE
			SYNTAX OCTET STRING
			ACCESS read-only
			STATUS mandatory
			DESCRIPTION
				"DESCRIPTION"
			::= { northboundReportAlarm 33 }

		
		-- 1.3.6.1.4.1.2011.2.15.1.7.3.34
		northboundReportAlarmAdditionalVB8 OBJECT-TYPE
			SYNTAX OCTET STRING
			ACCESS read-only
			STATUS mandatory
			DESCRIPTION
				"DESCRIPTION"
			::= { northboundReportAlarm 34 }

		
		-- 1.3.6.1.4.1.2011.2.15.1.7.3.35
		northboundReportAlarmAdditionalVB9 OBJECT-TYPE
			SYNTAX OCTET STRING
			ACCESS read-only
			STATUS mandatory
			DESCRIPTION
				"DESCRIPTION"
			::= { northboundReportAlarm 35 }

		
		-- 1.3.6.1.4.1.2011.2.15.1.7.3.36
		northboundReportAlarmAdditionalVB10 OBJECT-TYPE
			SYNTAX OCTET STRING
			ACCESS read-only
			STATUS mandatory
			DESCRIPTION
				"DESCRIPTION"
			::= { northboundReportAlarm 36 }

		
		-- 1.3.6.1.4.1.2011.2.15.1.7.4
		northboundSynchAlarm OBJECT IDENTIFIER ::= { nmNorthboundEvent 4 }

		
		-- 1.3.6.1.4.1.2011.2.15.1.7.4.1
		northBoundSynchAlarmCommand OBJECT-TYPE
			SYNTAX INTEGER
			ACCESS read-write
			STATUS mandatory
			DESCRIPTION
				"DESCRIPTION"
			::= { northboundSynchAlarm 1 }

		
		-- 1.3.6.1.4.1.2011.2.15.1.7.4.2
		northBoundSynchAlarmStartStatus OBJECT-TYPE
			SYNTAX INTEGER
			ACCESS read-only
			STATUS mandatory
			DESCRIPTION
				"It shows the result of alarm synchronization."
			::= { northboundSynchAlarm 2 }

		
		-- 1.3.6.1.4.1.2011.2.15.1.7.4.3
		northBoundSynchAlarmEndStatus OBJECT-TYPE
			SYNTAX INTEGER
			ACCESS read-only
			STATUS mandatory
			DESCRIPTION
				"It shows the result of alarm synchronization.
		    0 means the alarm synchronization successfully ended.
		    1 means the alarm synchronization is stopped by the NMS's command.
		    2 means some error occured during the alarm synchronization."
			::= { northboundSynchAlarm 3 }

		
		-- 1.3.6.1.4.1.2011.2.15.1.7.5
		northboundNotificationType OBJECT IDENTIFIER ::= { nmNorthboundEvent 5 }

		
		-- 1.3.6.1.4.1.2011.2.15.2
		nmModuleIdentity OBJECT IDENTIFIER ::= { netManagement 2 }

		
		-- 1.3.6.1.4.1.2011.2.15.3
		nmObjectGroup OBJECT IDENTIFIER ::= { netManagement 3 }

		
	
--
-- Trap definitions
--
	
		northBoundReportAlarm TRAP-TYPE 
			ENTERPRISE northboundNotificationType
			VARIABLES { northboundReportAlarmManagedObjectClass, northboundReportAlarmManagedObjectInstance, northboundReportAlarmEventType, northboundReportAlarmEventTime, northboundReportAlarmProbableCause, 
				northboundReportAlarmSpecificProblems, northboundReportAlarmPerceivedSeverity, northboundReportAlarmNotificationIdentifier, northboundReportAlarmCorrelatedNotifications, northboundReportAlarmProposedRepairActions, 
				northboundReportAlarmAdditionalText, northboundReportAlarmEmsName, northboundReportAlarmNEName, northboundReportAlarmDevLocation, northboundReportAlarmShelfName, 
				northboundReportAlarmBoardName, northboundReportAlarmPortType, northboundReportAlarmPortNumber, northboundReportAlarmLocation, northboundReportAlarmOperationAffected, 
				northboundReportAlarmID, northboundReportAlarmName, northboundReportAlarmIPAddress, northboundReportAlarmResourceID, northboundReportAlarmCleared, 
				northboundReportAlarmAdditionalVB1, northboundReportAlarmAdditionalVB2, northboundReportAlarmAdditionalVB3, northboundReportAlarmAdditionalVB4, northboundReportAlarmAdditionalVB5, 
				northboundReportAlarmAdditionalVB6, northboundReportAlarmAdditionalVB7, northboundReportAlarmAdditionalVB8, northboundReportAlarmAdditionalVB9, northboundReportAlarmAdditionalVB10, 
				northboundReportAlarmRackName }
			::=  1

		northBoundSynchAlarm TRAP-TYPE 
			ENTERPRISE northboundNotificationType
			VARIABLES { northboundReportAlarmManagedObjectClass, northboundReportAlarmManagedObjectInstance, northboundReportAlarmEventType, northboundReportAlarmEventTime, northboundReportAlarmProbableCause, 
				northboundReportAlarmSpecificProblems, northboundReportAlarmPerceivedSeverity, northboundReportAlarmNotificationIdentifier, northboundReportAlarmCorrelatedNotifications, northboundReportAlarmProposedRepairActions, 
				northboundReportAlarmAdditionalText, northboundReportAlarmEmsName, northboundReportAlarmNEName, northboundReportAlarmDevLocation, northboundReportAlarmShelfName, 
				northboundReportAlarmBoardName, northboundReportAlarmPortType, northboundReportAlarmPortNumber, northboundReportAlarmLocation, northboundReportAlarmOperationAffected, 
				northboundReportAlarmID, northboundReportAlarmName, northboundReportAlarmIPAddress, northboundReportAlarmResourceID, northboundReportAlarmCleared, 
				northboundReportAlarmAdditionalVB1, northboundReportAlarmAdditionalVB2, northboundReportAlarmAdditionalVB3, northboundReportAlarmAdditionalVB4, northboundReportAlarmAdditionalVB5, 
				northboundReportAlarmAdditionalVB6, northboundReportAlarmAdditionalVB7, northboundReportAlarmAdditionalVB8, northboundReportAlarmAdditionalVB9, northboundReportAlarmAdditionalVB10, 
				northboundReportAlarmRackName }
			::=  2

		northBoundSynchAlarmStart TRAP-TYPE 
			ENTERPRISE northboundNotificationType
			VARIABLES { northBoundSynchAlarmStartStatus }
			::=  3

		northBoundSynchAlarmEnd TRAP-TYPE 
			ENTERPRISE northboundNotificationType
			VARIABLES { northBoundSynchAlarmEndStatus }
			::=  4

	
	END

--
-- T2000-NETMANAGEMENT-MIB.mib
--
