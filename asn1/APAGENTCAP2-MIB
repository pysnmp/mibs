--------------------------------------------------------------------------------
-- ACMEPACKET-AGENTCAP2-MIB.txt:  Acme Packet agent capability2 MIB file
--
-- Copyright (c) by Oracle Communications
-- All rights reserved.
---------------------------------------------------------------


APAGENTCAP2-MIB DEFINITIONS ::= BEGIN

IMPORTS
	MODULE-IDENTITY, OBJECT-TYPE, NOTIFICATION-TYPE,
	enterprises, snmpModules, mib-2 
		 				FROM SNMPv2-SMI
	MODULE-COMPLIANCE, AGENT-CAPABILITIES
						FROM SNMPv2-CONF
	acmepacketAgentCapability 	FROM ACMEPACKET-SMI;

apAgentCap2Module MODULE-IDENTITY
		LAST-UPDATED	"202203240000Z"
		ORGANIZATION 	"Oracle Communications"
		CONTACT-INFO
			"           	Customer Service
		 	Postal:		Oracle Communications
					100 Crosby Drive 
					Bedford, MA 01730
					US
		    	Tel:		1-800-633-0738
			Url:		www.oracle.com
		 	E-mail:		support@oracle.com"
		DESCRIPTION	
			" Agent capability2 MIB for Oracle Communications Acme Packet SBCs."
                REVISION "202010260000Z" 			
                DESCRIPTION
			"Added apStirCap"
                REVISION "202107060000Z" 			
                DESCRIPTION
			"Added apStirCap2"
                REVISION "202202160000Z" 			
                DESCRIPTION
			"Added new capability objects apSipMSRPKPIStatsCap for MSRP statistics."
                REVISION "202203240000Z"
                DESCRIPTION
                        "Added apNSEPRealmKPIStatsCap and apSmgmtNSEPOutboundSession."

		::= { acmepacketAgentCapability 2}


-- standard mibs modules
apIPForwardMibCapabilities     OBJECT IDENTIFIER ::= { apAgentCap2Module 1 }

--------------------------------------------------------------
-- 
-- Following are the Standard Groups that we supports
--
--------------------------------------------------------------


apIpForwardCap AGENT-CAPABILITIES
            PRODUCT-RELEASE     "Oracle Communications Acme Packet SBC"

            STATUS          	current
            DESCRIPTION     	"Acme Packet Agent Capability IP-FORWARD support."
		SUPPORTS	IP-FORWARD-MIB
		INCLUDES	{ inetForwardCidrRouteGroup, ipForwardCidrRouteGroup }

            ::= { apIPForwardMibCapabilities 1 }

apAppsStirMibCapabilities     OBJECT IDENTIFIER ::= { apAgentCap2Module 2 }

apStirCap AGENT-CAPABILITIES
            PRODUCT-RELEASE     "Oracle Communications Acme Packet SBC"

            STATUS          	current
            DESCRIPTION     	"Acme Packet Agent Capability Stir MIB support."
		SUPPORTS	APAPPS-MIB
		INCLUDES	{ apAppsStirServerStatsGroup, apAppsStirNotificationsGroup }

            ::= { apAppsStirMibCapabilities 1 }

apStirCap2 AGENT-CAPABILITIES
	    PRODUCT-RELEASE     "Oracle Communications Acme Packet SBC"

            STATUS              current
            DESCRIPTION         "Acme Packet Agent Capability Stir Agent MIB support."
                SUPPORTS        APAPPS-MIB
                INCLUDES        { apAppsStirAgentStatsGroup, apAppsStirSipInterfaceStatsGroup,
					 apAppsStirRealmStatsGroup, apAppsStirSystemStatsGroup }

            ::= { apAppsStirMibCapabilities 2 }

apMSRPKPIMibCapabilities     OBJECT IDENTIFIER ::= { apAgentCap2Module 3 }

apMSRPKPIStatsCap AGENT-CAPABILITIES
	    PRODUCT-RELEASE     "Oracle Communications Acme Packet SBC"

            STATUS              current
            DESCRIPTION         "Acme Packet Agent Capability for MSRP KPI statistics  MIB."
                SUPPORTS        APAPPS-MIB
                INCLUDES        { apAppsMSRPKPISystemStatsGroup, apAppsMSRPKPIRealmStatsGroup } 

            ::= { apMSRPKPIMibCapabilities 1 }

apNSEPRealmKPIMibCapabilities   OBJECT IDENTIFIER ::= { apAgentCap2Module 4 }

apNSEPRealmKPIStatsCap    AGENT-CAPABILITIES
            PRODUCT-RELEASE     "Oracle Communications Acme Packet SBC"
            STATUS              current
            DESCRIPTION         "Acme Packet Agent Capability for NSEP Realm
                                KPI statistics MIB."
            SUPPORTS        APAPPS-MIB
            INCLUDES        { apNSEPRealmStatsGroup }
            ::= {apNSEPRealmKPIMibCapabilities 1}

apNSEPOutboundSessionMibCapabilities  OBJECT IDENTIFIER ::= {apAgentCap2Module 5 }

apSmgmtNSEPOutboundSession      AGENT-CAPABILITIES
            PRODUCT-RELEASE     "Oracle Communications Acme Packet SBC"
            STATUS              current
            DESCRIPTION         "Acme Packet Agent Capability for NSEP
                                Outbound KPI statistics MIB."
            SUPPORTS        APSYSMGMT-MIB
            INCLUDES        {
                            apSysMgmtNSEPOutboundStatsGroup
                            }
            ::= { apNSEPOutboundSessionMibCapabilities 1}


END
