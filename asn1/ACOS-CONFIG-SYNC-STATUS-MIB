ACOS-CONFIG-SYNC-STATUS-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		configSyncStatusModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "configSyncStatusModule OID for ACOS"
				::=  {  acosSchema 170 }

configSyncStatus		 OBJECT IDENTIFIER ::= { configSyncStatusModule 1}

configSyncStatusOperConfigSyncListTable OBJECT-TYPE
	 SYNTAX SEQUENCE OF ConfigSyncStatusOperConfigSyncListEntry
	 MAX-ACCESS not-accessible
	 STATUS current
	 DESCRIPTION
		 "Display config sync status for all partitions from object 'config-sync-status'"
	::= {configSyncStatus 2}

configSyncStatusOperConfigSyncListEntry OBJECT-TYPE
	SYNTAX ConfigSyncStatusOperConfigSyncListEntry
	MAX-ACCESS not-accessible
	STATUS current
	DESCRIPTION
		"The configSyncStatusOperConfigSyncList entry:config-sync-list"
	INDEX {
		configSyncStatusOperConfigSyncListSlotId,
		configSyncStatusOperConfigSyncListConfigSyncListListId
	}
	::= { configSyncStatusOperConfigSyncListTable 1}

ConfigSyncStatusOperConfigSyncListEntry ::=
	SEQUENCE {
		configSyncStatusOperConfigSyncListSlotId Integer32,
		configSyncStatusOperConfigSyncListConfigSyncListListId Integer32,
		configSyncStatusOperConfigSyncListPartitionName	DisplayString,
		configSyncStatusOperConfigSyncListRunSyncStatus	DisplayString,
		configSyncStatusOperConfigSyncListStartupSyncStatus	DisplayString
	}

configSyncStatusOperConfigSyncListSlotId OBJECT-TYPE
	SYNTAX Integer32
	MAX-ACCESS read-only
	STATUS current
	DESCRIPTION
		""
	::= { configSyncStatusOperConfigSyncListEntry 1}

configSyncStatusOperConfigSyncListConfigSyncListListId OBJECT-TYPE
	SYNTAX Integer32
	MAX-ACCESS read-only
	STATUS current
	DESCRIPTION
		""
	::= { configSyncStatusOperConfigSyncListEntry 2}

configSyncStatusOperConfigSyncListPartitionName OBJECT-TYPE
	SYNTAX DisplayString
	MAX-ACCESS read-only
	STATUS current
	DESCRIPTION
		"partition-name"
	::= { configSyncStatusOperConfigSyncListEntry 3}

configSyncStatusOperConfigSyncListRunSyncStatus OBJECT-TYPE
	SYNTAX DisplayString
	MAX-ACCESS read-only
	STATUS current
	DESCRIPTION
		"run-sync-status"
	::= { configSyncStatusOperConfigSyncListEntry 4}

configSyncStatusOperConfigSyncListStartupSyncStatus OBJECT-TYPE
	SYNTAX DisplayString
	MAX-ACCESS read-only
	STATUS current
	DESCRIPTION
		"startup-sync-status"
	::= { configSyncStatusOperConfigSyncListEntry 5}

END
