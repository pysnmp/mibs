--
-- RS-XX9-ISDBT-MIB.mi2
-- MIB generated by MG-SOFT Visual MIB Builder 2010 Version 8.0  Build 403
-- Wednesday, June 03, 2015 at 14:54:48
--

-- *****************************************************************************
-- *****************************************************************************
-- **
-- **  COPYRIGHT      (c) 2012 Rohde & Schwarz GmbH & Co. KG
-- **                          Muehldorfstrasse 15
-- **    R & S                 D-81671 Muenchen
-- **
-- *****************************************************************************
-- **
-- **  MODULE         RS-XX9-ISDBT-MIB
-- **  
-- *****************************************************************************
-- *****************************************************************************

    RS-XX9-ISDBT-MIB DEFINITIONS ::= BEGIN
 
        IMPORTS
            commonNotificationAlarmClass            
                FROM RS-XX9-COMMON-MIB            
            rsXx9IsdbT, rsXx9MibModule            
                FROM RS-XX9-SMI-MIB            
            NotificationClass, IndexAB, IndexTransmitter, NotificationMask, NotificationPriority, 
            NotificationState, SwitchOnOff            
                FROM RS-XX9-TC-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI            
            TruthValue, TEXTUAL-CONVENTION            
                FROM SNMPv2-TC;
    
    
        rsXx9IsdbtMibModule MODULE-IDENTITY 
            LAST-UPDATED "201506031500Z"		-- June 03, 2015 at 15:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines ISDB-T specific objects
                of XX9000 transmitting systems from Rohde & Schwarz.
                
                The following MIBs are related to this:
                - RS-COMMON-MIB         - mandatory for this MIB
                - RS-XX9-SMI-MIB        - mandatory for this MIB
                - RS-XX9-TC-MIB         - mandatory for this MIB
                - RS-XX9-COMMON-MIB     - mandatory for this MIB"
            REVISION "201506031500Z"		-- June 03, 2015 at 15:00 GMT
            DESCRIPTION 
                "add isdbtOutStatusEwbsActFlag"
            REVISION "201412221600Z"		-- December 22, 2014 at 16:00 GMT
            DESCRIPTION 
                "updated description texts
                "
            REVISION "201403251600Z"		-- March 25, 2014 at 16:00 GMT
            DESCRIPTION 
                "Initial release.
                added isdbtNitRestampingTable"
            REVISION "201205141000Z"		-- May 14, 2012 at 10:00 GMT
            DESCRIPTION 
                "Preliminary release."
            ::= { rsXx9MibModule 8 }

        
    
--
-- Textual conventions
--
    
        IsdbtMode ::= TEXTUAL-CONVENTION
            STATUS current
            DESCRIPTION 
                "Selects the FFT size:
                mode1(2) - 2048 carriers
                mode2(3) - 4096 carriers
                mode3(4) - 8192 carriers"
            SYNTAX INTEGER
                {
                mode1(2),
                mode2(3),
                mode3(4)
                }

        IsdbtGuardInterval ::= TEXTUAL-CONVENTION
            STATUS current
            DESCRIPTION 
                "The Guard Interval determines the time span between signals
                for multicarrier modulation, in which no information is transmitted.
                The larger the time span is, the lower the risk of interference
                and the lower the data transfer rate.
                The values are a fraction of the symbol period.
                Ideally, you select a value that is larger than the channel spread. "
            SYNTAX INTEGER
                {
                oneDiv32(1),
                oneDiv16(2),
                oneDiv8(3),
                oneDiv4(4)
                }

        IsdbtLayer ::= TEXTUAL-CONVENTION
            STATUS current
            DESCRIPTION 
                "Description."
            SYNTAX INTEGER
                {
                a(1),
                b(2),
                c(3)
                }

        IsdbtConstellation ::= TEXTUAL-CONVENTION
            STATUS current
            DESCRIPTION 
                "Description."
            SYNTAX INTEGER
                {
                dqpsk(2),
                qpsk(3),
                qam16(4),
                qam64(5)
                }

        IsdbtCodeRate ::= TEXTUAL-CONVENTION
            STATUS current
            DESCRIPTION 
                "The coderate sets the ratio between payload
                and error correction information."
            SYNTAX INTEGER
                {
                oneHalf(1),
                twoThird(3),
                threeFourth(4),
                fiveSixth(6),
                sevenEighth(7)
                }

        IsdbtNitRestampingSource ::= TEXTUAL-CONVENTION
            STATUS current
            DESCRIPTION 
                "Description."
            SYNTAX INTEGER
                {
                bts(1),
                manual(2)
                }

    
--
-- Node definitions
--
    
        rsXx9IsdbtNotifications OBJECT IDENTIFIER ::= { rsXx9IsdbT 0 }

        
        isdbtIIP NOTIFICATION-TYPE
            OBJECTS { commonNotificationAlarmClass, isdbtStatusNotificationPriority, isdbtStatusNotificationState }
            STATUS current
            DESCRIPTION 
                "Shows whether ISDB-T information packets (IIP) with the appropriate ID
                are present in the transport stream
                Possible values:
                off(2)     - isdbtCfgCoderSettingsSource is manual(2)
                fault(3)   - the input data does not contain a IIP
                warning(4) - no SFN info
                ok(5)      - IIP found
                
                Notification class: warning"
            ::= { rsXx9IsdbtNotifications 1 }

        
        isdbtFrameCounter NOTIFICATION-TYPE
            OBJECTS { commonNotificationAlarmClass, isdbtStatusNotificationPriority, isdbtStatusNotificationState }
            STATUS current
            DESCRIPTION 
                "Shows the correctness of TSPs.
                
                Possible values:
                off(2)
                warning(4) - incorrect or missing TSP detected
                ok(5)
                
                Notification class: warning"
            ::= { rsXx9IsdbtNotifications 2 }

        
        isdbtEquipmentId NOTIFICATION-TYPE
            OBJECTS { commonNotificationAlarmClass, isdbtStatusNotificationPriority, isdbtStatusNotificationState }
            STATUS current
            DESCRIPTION 
                "Shows the existence of SFN information matching the
                selected equipment ID.
                
                Possible values:
                off(2)     - isdbtLocalizationEquipmentControl is off(2)
                             or isdbtCfgCoderSettingsSource is manual(2)
                warning(4) - no matching SFN information
                ok(5)
                
                Notification class: warning"
            ::= { rsXx9IsdbtNotifications 3 }

        
        isdbtManualConfiguration NOTIFICATION-TYPE
            OBJECTS { commonNotificationAlarmClass, isdbtStatusNotificationPriority, isdbtStatusNotificationState }
            STATUS current
            DESCRIPTION 
                "Indicates whether the configured ISDB-T configuration
                is consistent and valid over all three layers.
                If an error is displayed, check whether the sum of all
                segments over the three layers is exactly 13.
                
                Possible values:
                off(2)     - 
                warning(4) - not valid
                ok(5)      - valid
                
                Notification class: warning"
            ::= { rsXx9IsdbtNotifications 4 }

        
        isdbtActiveConfiguration NOTIFICATION-TYPE
            OBJECTS { commonNotificationAlarmClass, isdbtStatusNotificationPriority, isdbtStatusNotificationState }
            STATUS current
            DESCRIPTION 
                "Indicates whether the active ISDB-T configuration
                is consistent and valid over all three layers.
                If an error is displayed, check whether the sum of all
                segments over the three layers is exactly 13.
                
                Possible values:
                off(2)     - 
                warning(4) - not valid
                ok(5)      - valid
                
                Notification class: warning"
            ::= { rsXx9IsdbtNotifications 5 }

        
        isdbtTest NOTIFICATION-TYPE
            OBJECTS { commonNotificationAlarmClass, isdbtStatusNotificationPriority, isdbtStatusNotificationState }
            STATUS current
            DESCRIPTION 
                "Possible values:
                off(2)     - no test signal generation
                warning(4) - test signal generation is activated
                
                Notification class: warning"
            ::= { rsXx9IsdbtNotifications 6 }

        
        rsXx9IsdbtObjects OBJECT IDENTIFIER ::= { rsXx9IsdbT 1 }

        
        isdbtStatus OBJECT IDENTIFIER ::= { rsXx9IsdbtObjects 1 }

        
        isdbtStatusNotificationTable OBJECT-TYPE
            SYNTAX SEQUENCE OF IsdbtStatusNotificationEntry
            MAX-ACCESS not-accessible
            STATUS current
            DESCRIPTION
                "The context information/configuration for the
                ISDB-T status notifications."
            ::= { isdbtStatus 1 }

        
        isdbtStatusNotificationEntry OBJECT-TYPE
            SYNTAX IsdbtStatusNotificationEntry
            MAX-ACCESS not-accessible
            STATUS current
            DESCRIPTION
                "An entry in the isdbtStatusNotificationTable."
            INDEX { isdbtStatusNotificationTxIdx, isdbtStatusNotificationExcIdx, isdbtStatusNotificationIdx }
            ::= { isdbtStatusNotificationTable 1 }

        
        IsdbtStatusNotificationEntry ::=
            SEQUENCE { 
                isdbtStatusNotificationTxIdx
                    IndexTransmitter,
                isdbtStatusNotificationExcIdx
                    IndexAB,
                isdbtStatusNotificationIdx
                    Unsigned32,
                isdbtStatusNotificationName
                    INTEGER,
                isdbtStatusNotificationMask
                    NotificationMask,
                isdbtStatusNotificationPriority
                    NotificationPriority,
                isdbtStatusNotificationState
                    NotificationState
             }

        isdbtStatusNotificationTxIdx OBJECT-TYPE
            SYNTAX IndexTransmitter
            MAX-ACCESS not-accessible
            STATUS current
            DESCRIPTION
                "The transmitter index."
            ::= { isdbtStatusNotificationEntry 1 }

        
        isdbtStatusNotificationExcIdx OBJECT-TYPE
            SYNTAX IndexAB
            MAX-ACCESS not-accessible
            STATUS current
            DESCRIPTION
                "This index distinguishes the exiters.
                Necessary if you have dual drive transmitters."
            ::= { isdbtStatusNotificationEntry 2 }

        
        isdbtStatusNotificationIdx OBJECT-TYPE
            SYNTAX Unsigned32 (1..6)
            MAX-ACCESS not-accessible
            STATUS current
            DESCRIPTION
                "The notification number as below rsXx9IsdbtNotifications.
                This is a helper column and therefore not-accessible."
            ::= { isdbtStatusNotificationEntry 3 }

        
        isdbtStatusNotificationName OBJECT-TYPE
            SYNTAX INTEGER
                {
                isdbtIIP(1),
                isdbtFrameCounter(2),
                isdbtEquipmentId(3),
                isdbtManualConfiguration(4),
                isdbtActiveConfiguration(5),
                isdbtTest(6)
                }
            MAX-ACCESS read-write
            STATUS current
            DESCRIPTION
                "The notification number as an enumeration.
                The enumeration correlates with the notifications under rsXx9IsdbtNotifications."
            ::= { isdbtStatusNotificationEntry 4 }

        
        isdbtStatusNotificationMask OBJECT-TYPE
            SYNTAX NotificationMask
            MAX-ACCESS read-write
            STATUS current
            DESCRIPTION
                "See TextualConvention for details."
            ::= { isdbtStatusNotificationEntry 5 }

        
        isdbtStatusNotificationPriority OBJECT-TYPE
            SYNTAX NotificationPriority
            MAX-ACCESS read-write
            STATUS current
            DESCRIPTION
                "See TextualConvention for details."
            ::= { isdbtStatusNotificationEntry 6 }

        
        isdbtStatusNotificationState OBJECT-TYPE
            SYNTAX NotificationState
            MAX-ACCESS read-only
            STATUS current
            DESCRIPTION
                "See TextualConvention for details."
            ::= { isdbtStatusNotificationEntry 7 }

        
        isdbtStateTable OBJECT-TYPE
            SYNTAX SEQUENCE OF IsdbtStateEntry
            MAX-ACCESS not-accessible
            STATUS current
            DESCRIPTION
                "ISDB-T state values."
            ::= { isdbtStatus 2 }

        
        isdbtStateEntry OBJECT-TYPE
            SYNTAX IsdbtStateEntry
            MAX-ACCESS not-accessible
            STATUS current
            DESCRIPTION
                "An entry in the isdbtStateTable."
            INDEX { isdbtStatusNotificationTxIdx, isdbtStatusNotificationExcIdx }
            ::= { isdbtStateTable 1 }

        
        IsdbtStateEntry ::=
            SEQUENCE { 
                isdbtStTxDelayOffset
                    Integer32
             }

        isdbtStTxDelayOffset OBJECT-TYPE
            SYNTAX Integer32
            UNITS "1/10 micro second"
            MAX-ACCESS read-only
            STATUS current
            DESCRIPTION
                "Transmitting time shift compared to other
                transmitters in the ISDB-T network."
            ::= { isdbtStateEntry 1 }

        
        isdbtSetup OBJECT IDENTIFIER ::= { rsXx9IsdbtObjects 2 }

        
        isdbtConfigurationTable OBJECT-TYPE
            SYNTAX SEQUENCE OF IsdbtConfigurationEntry
            MAX-ACCESS not-accessible
            STATUS current
            DESCRIPTION
                "ISDB-T configuration."
            ::= { isdbtSetup 1 }

        
        isdbtConfigurationEntry OBJECT-TYPE
            SYNTAX IsdbtConfigurationEntry
            MAX-ACCESS not-accessible
            STATUS current
            DESCRIPTION
                "An entry in the isdbtConfigurationTable."
            INDEX { isdbtCfgTxIdx, isdbtCfgExcIdx }
            ::= { isdbtConfigurationTable 1 }

        
        IsdbtConfigurationEntry ::=
            SEQUENCE { 
                isdbtCfgTxIdx
                    IndexTransmitter,
                isdbtCfgExcIdx
                    IndexAB,
                isdbtCfgNetworkMode
                    INTEGER,
                isdbtCfgCoderSettingsSource
                    INTEGER,
                isdbtCfgIipID
                    Unsigned32,
                isdbtCfgBandwidth
                    INTEGER
             }

        isdbtCfgTxIdx OBJECT-TYPE
            SYNTAX IndexTransmitter
            MAX-ACCESS not-accessible
            STATUS current
            DESCRIPTION
                "The transmitter index."
            ::= { isdbtConfigurationEntry 1 }

        
        isdbtCfgExcIdx OBJECT-TYPE
            SYNTAX IndexAB
            MAX-ACCESS not-accessible
            STATUS current
            DESCRIPTION
                "This index distinguishes the exiters.
                Necessary if you have dual drive transmitters."
            ::= { isdbtConfigurationEntry 2 }

        
        isdbtCfgNetworkMode OBJECT-TYPE
            SYNTAX INTEGER
                {
                mfn(1),
                dynamicSfn(2),
                staticSfn(3),
                automatic(4)
                }
            MAX-ACCESS read-write
            STATUS current
            DESCRIPTION
                "It can be switched between Single Frequency Networks and
                Multiple Frequency Networks."
            ::= { isdbtConfigurationEntry 3 }

        
        isdbtCfgCoderSettingsSource OBJECT-TYPE
            SYNTAX INTEGER
                {
                iip(1),
                manual(2)
                }
            MAX-ACCESS read-write
            STATUS current
            DESCRIPTION
                "Selects the source for the TMCC (Transmission and Multiplexing
                Configuration Control) input parameter for the ISDB-T coder.
                
                iip(1)    - parameters are read out of the IIP in the transmission
                manual(2) - parameters are configured in the transmitter"
            ::= { isdbtConfigurationEntry 4 }

        
        isdbtCfgIipID OBJECT-TYPE
            SYNTAX Unsigned32 (0..65535)
            MAX-ACCESS read-write
            STATUS current
            DESCRIPTION
                "PID (packet ID) number for the IIP (ISDB-T information packet)
                in the input data stream.
                Requirement is that isdbtCfgCoderSettingsSource is iip(1)."
            ::= { isdbtConfigurationEntry 5 }

        
        isdbtCfgBandwidth OBJECT-TYPE
            SYNTAX INTEGER
                {
                mhz6(5),
                mhz7(6),
                mhz8(7)
                }
            MAX-ACCESS read-write
            STATUS current
            DESCRIPTION
                "Description."
            ::= { isdbtConfigurationEntry 6 }

        
        isdbtLocalizationTable OBJECT-TYPE
            SYNTAX SEQUENCE OF IsdbtLocalizationEntry
            MAX-ACCESS not-accessible
            STATUS current
            DESCRIPTION
                "ISDB-T localization."
            ::= { isdbtSetup 2 }

        
        isdbtLocalizationEntry OBJECT-TYPE
            SYNTAX IsdbtLocalizationEntry
            MAX-ACCESS not-accessible
            STATUS current
            DESCRIPTION
                "An entry in the isdbtLocalizationTable."
            AUGMENTS { isdbtConfigurationEntry }
            ::= { isdbtLocalizationTable 1 }

        
        IsdbtLocalizationEntry ::=
            SEQUENCE { 
                isdbtLocalizationEquipmentControl
                    SwitchOnOff,
                isdbtLocalizationEquipmentID
                    Unsigned32
             }

        isdbtLocalizationEquipmentControl OBJECT-TYPE
            SYNTAX SwitchOnOff
            MAX-ACCESS read-write
            STATUS current
            DESCRIPTION
                "Activates or deactivates the device ID.
                This way transmitter-specific settings may be configured via
                the ISDB-T information packet present in the transport stream.
                Operation is possible if isdbtCfgCoderSettingsSource is iip(1)."
            ::= { isdbtLocalizationEntry 1 }

        
        isdbtLocalizationEquipmentID OBJECT-TYPE
            SYNTAX Unsigned32 (0..65535)
            MAX-ACCESS read-write
            STATUS current
            DESCRIPTION
                "A unique device ID, to be able to reference special settings
                of the IIP (ISDB-T information packet). "
            ::= { isdbtLocalizationEntry 2 }

        
        isdbtTmccTable OBJECT-TYPE
            SYNTAX SEQUENCE OF IsdbtTmccEntry
            MAX-ACCESS not-accessible
            STATUS current
            DESCRIPTION
                "TMCC (transmission and multiplexing configuration control) configuration."
            ::= { isdbtSetup 3 }

        
        isdbtTmccEntry OBJECT-TYPE
            SYNTAX IsdbtTmccEntry
            MAX-ACCESS not-accessible
            STATUS current
            DESCRIPTION
                "An entry in the isdbtTmccTable."
            AUGMENTS { isdbtConfigurationEntry }
            ::= { isdbtTmccTable 1 }

        
        IsdbtTmccEntry ::=
            SEQUENCE { 
                isdbtTmccNext
                    INTEGER,
                isdbtTmccMode
                    IsdbtMode,
                isdbtTmccGuardInterval
                    IsdbtGuardInterval,
                isdbtTmccPartialReception
                    SwitchOnOff
             }

        isdbtTmccNext OBJECT-TYPE
            SYNTAX INTEGER
                {
                off(1),
                active(2),
                automatic(3)
                }
            MAX-ACCESS read-write
            STATUS current
            DESCRIPTION
                "Transmission and Multiplexing Configuration Control:
                off(1)       - all TMCC NEXT is set to unused.
                active(2)    - the TMCC NEXT contains the active coder setup.
                automatic(3) - the TMCC NEXT follows the IIP TMCC NEXT signalisation
                               if available and used for coder source, otherwise the
                               active coder setup is used."
            ::= { isdbtTmccEntry 1 }

        
        isdbtTmccMode OBJECT-TYPE
            SYNTAX IsdbtMode
            MAX-ACCESS read-write
            STATUS current
            DESCRIPTION
                "see textual convention"
            ::= { isdbtTmccEntry 2 }

        
        isdbtTmccGuardInterval OBJECT-TYPE
            SYNTAX IsdbtGuardInterval
            MAX-ACCESS read-write
            STATUS current
            DESCRIPTION
                "see textual convention"
            ::= { isdbtTmccEntry 3 }

        
        isdbtTmccPartialReception OBJECT-TYPE
            SYNTAX SwitchOnOff
            MAX-ACCESS read-write
            STATUS current
            DESCRIPTION
                "If layer A for mobile reception is to be used (1-segment receiver),
                set 'Partial Reception' to on(1).
                In this case, segment 0 is arranged in the band center.
                The value can be entered manually and is used for TMCC NEXT
                (transmission and multiplexing configuration control NEXT)
                if isdbtTmccNext is set to active(2)."
            ::= { isdbtTmccEntry 4 }

        
        isdbtTmccLayerTable OBJECT-TYPE
            SYNTAX SEQUENCE OF IsdbtTmccLayerEntry
            MAX-ACCESS not-accessible
            STATUS current
            DESCRIPTION
                "TMCC layer configuration."
            ::= { isdbtSetup 4 }

        
        isdbtTmccLayerEntry OBJECT-TYPE
            SYNTAX IsdbtTmccLayerEntry
            MAX-ACCESS not-accessible
            STATUS current
            DESCRIPTION
                "An entry in the isdbtTmccLayerTable."
            INDEX { isdbtCfgTxIdx, isdbtCfgExcIdx, isdbtTmccLayerIdx }
            ::= { isdbtTmccLayerTable 1 }

        
        IsdbtTmccLayerEntry ::=
            SEQUENCE { 
                isdbtTmccLayerIdx
                    IsdbtLayer,
                isdbtTmccLayerSegments
                    Unsigned32,
                isdbtTmccLayerConstellation
                    IsdbtConstellation,
                isdbtTmccLayerCodeRate
                    IsdbtCodeRate,
                isdbtTmccLayerTimeInterleaver
                    Unsigned32
             }

        isdbtTmccLayerIdx OBJECT-TYPE
            SYNTAX IsdbtLayer
            MAX-ACCESS not-accessible
            STATUS current
            DESCRIPTION
                "TMCC layer index."
            ::= { isdbtTmccLayerEntry 3 }

        
        isdbtTmccLayerSegments OBJECT-TYPE
            SYNTAX Unsigned32 (0..13)
            MAX-ACCESS read-write
            STATUS current
            DESCRIPTION
                "Number of segments used for the layer concerned.
                The allocation of segments to the layers is subject to conditions:
                0 - layer is deactivated.
                For layer A, 0 is not permitted.
                For layer B, 0 is possible only if layer C also has 0 segments.
                The sum of all the segments from all the active layers must always be 13.
                The segments can be distributed over 1, 2 or 3 layers.
                An allocation of 1 single segment is possible only for layer A.
                This is only allowed if isdbtTmccPartialReception is on(1).
                The remaining 12 segments can be distributed over layers B and C
                according to the above rules."
            ::= { isdbtTmccLayerEntry 4 }

        
        isdbtTmccLayerConstellation OBJECT-TYPE
            SYNTAX IsdbtConstellation
            MAX-ACCESS read-write
            STATUS current
            DESCRIPTION
                "Configure the modulation format with this parameter.
                qpsk(3)  - is very fail-safe, but has only a small data rate.
                qam64(5) - can transmit very large data rates if you expect faults
                           on the transmission link.
                qam16(4) - is a compromise between the two other setting values.
                The value can be entered manually and is used for TMCC NEXT
                (transmission and multiplexing configuration control NEXT)
                if isdbtTmccNext is set to active(2)."
            ::= { isdbtTmccLayerEntry 5 }

        
        isdbtTmccLayerCodeRate OBJECT-TYPE
            SYNTAX IsdbtCodeRate
            MAX-ACCESS read-write
            STATUS current
            DESCRIPTION
                "see textual convention."
            ::= { isdbtTmccLayerEntry 6 }

        
        isdbtTmccLayerTimeInterleaver OBJECT-TYPE
            SYNTAX Unsigned32 (0..2 | 4 | 8 | 16)
            MAX-ACCESS read-write
            STATUS current
            DESCRIPTION
                "To reduce the susceptibility to faults when there is noise,
                the time interleaver mixes the user data in a data block.
                0, 1, 2, 4, 8, and 16 can be selected as conversion length.
                0 means that no conversion take place,
                16 corresponds to the highest degree of conversion.
                This offers the greatest protection, but also the greatest latency.
                The value can be entered manually and is used for TMCC NEXT
                (transmission and multiplexing configuration control NEXT)
                if isdbtTmccNext is set to active(2)."
            ::= { isdbtTmccLayerEntry 7 }

        
        isdbtTestTable OBJECT-TYPE
            SYNTAX SEQUENCE OF IsdbtTestEntry
            MAX-ACCESS not-accessible
            STATUS current
            DESCRIPTION
                "Configures the test mode of the exciter."
            ::= { isdbtSetup 5 }

        
        isdbtTestEntry OBJECT-TYPE
            SYNTAX IsdbtTestEntry
            MAX-ACCESS not-accessible
            STATUS current
            DESCRIPTION
                "An entry in the isdbtTestTable."
            AUGMENTS { isdbtConfigurationEntry }
            ::= { isdbtTestTable 1 }

        
        IsdbtTestEntry ::=
            SEQUENCE { 
                isdbtTestGeneration
                    SwitchOnOff,
                isdbtTestMode
                    INTEGER
             }

        isdbtTestGeneration OBJECT-TYPE
            SYNTAX SwitchOnOff
            MAX-ACCESS read-write
            STATUS obsolete
            DESCRIPTION
                "Switches test signal generation on or off."
            ::= { isdbtTestEntry 1 }

        
        isdbtTestMode OBJECT-TYPE
            SYNTAX INTEGER
                {
                off(1),
                testMode0(4),
                testMode1(5)
                }
            MAX-ACCESS read-write
            STATUS current
            DESCRIPTION
                "off(1)       - no test mode
                testMode0(4) - For activating a test sequence with three layers,
                            ISDB-T mode 1 and guard interval 1/4.
                            Layer A: 1 segment,  DQPSK, code rate 1/2, time interleaver: 0
                            Layer B: 7 segments, 16QAM, code rate 7/8, time interleaver: 0
                            Layer C: 5 segments, 64QAM, code rate 2/3, time interleaver: 0
                testMode1(5) - For activating a test sequence with one layer,
                            ISDB-T mode 1 and guard interval 1/4.
                            Layer A: 13 segments, QPSK, code rate 1/2, time interleaver: 0"
            ::= { isdbtTestEntry 2 }

        
        isdbtNitRestampingTable OBJECT-TYPE
            SYNTAX SEQUENCE OF IsdbtNitRestampingEntry
            MAX-ACCESS not-accessible
            STATUS current
            DESCRIPTION
                "Description."
            ::= { isdbtSetup 6 }

        
        isdbtNitRestampingEntry OBJECT-TYPE
            SYNTAX IsdbtNitRestampingEntry
            MAX-ACCESS not-accessible
            STATUS current
            DESCRIPTION
                "Description."
            AUGMENTS { isdbtConfigurationEntry }
            ::= { isdbtNitRestampingTable 1 }

        
        IsdbtNitRestampingEntry ::=
            SEQUENCE { 
                isdbtNitNetworkIdSource
                    IsdbtNitRestampingSource,
                isdbtNitManualNetworkId
                    Unsigned32,
                isdbtNitTransportStreamIdSource
                    IsdbtNitRestampingSource,
                isdbtNitTransportManualStreamId
                    Unsigned32,
                isdbtNitAreaCodeSource
                    IsdbtNitRestampingSource,
                isdbtNitManualAreaCode
                    Unsigned32,
                isdbtNitFrequencySource
                    IsdbtNitRestampingSource,
                isdbtNitManualFrequency
                    Unsigned32,
                isdbtNitVirtualChannelSource
                    IsdbtNitRestampingSource,
                isdbtNitManualVirtualChannel
                    Unsigned32
             }

        isdbtNitNetworkIdSource OBJECT-TYPE
            SYNTAX IsdbtNitRestampingSource
            MAX-ACCESS read-write
            STATUS current
            DESCRIPTION
                "This allows to enable the localization of the network id using a manual setup."
            ::= { isdbtNitRestampingEntry 1 }

        
        isdbtNitManualNetworkId OBJECT-TYPE
            SYNTAX Unsigned32 (0..65535)
            MAX-ACCESS read-write
            STATUS current
            DESCRIPTION
                "This is a label to identify the network. Localization is done within each NIT.
                Only valid, if isdbtNitNetworkIdSource is set to manual(2).
                "
            ::= { isdbtNitRestampingEntry 2 }

        
        isdbtNitTransportStreamIdSource OBJECT-TYPE
            SYNTAX IsdbtNitRestampingSource
            MAX-ACCESS read-write
            STATUS current
            DESCRIPTION
                "This allows to enable the localization of the transport stream id using a manual setup."
            ::= { isdbtNitRestampingEntry 3 }

        
        isdbtNitTransportManualStreamId OBJECT-TYPE
            SYNTAX Unsigned32 (0..65535)
            MAX-ACCESS read-write
            STATUS current
            DESCRIPTION
                "This is a label to identify the transport stream from any other multiplex within the delivery system. Localization is done within each NIT, PAT, SDT, EIT, RST, PCAT and LDT.
                Only valid, if isdbtNitTransportStreamIdSource is set to manual(2).
                "
            ::= { isdbtNitRestampingEntry 4 }

        
        isdbtNitAreaCodeSource OBJECT-TYPE
            SYNTAX IsdbtNitRestampingSource
            MAX-ACCESS read-write
            STATUS current
            DESCRIPTION
                "This allows to enable the localization of the area code using a manual setup."
            ::= { isdbtNitRestampingEntry 5 }

        
        isdbtNitManualAreaCode OBJECT-TYPE
            SYNTAX Unsigned32 (0..4095)
            MAX-ACCESS read-write
            STATUS current
            DESCRIPTION
                "This is the service area code from terrestrial delivery system descriptor. Localization is done within each NIT.
                Only valid, if isdbtNitAreaCodeSource is set to manual(2).
                "
            ::= { isdbtNitRestampingEntry 6 }

        
        isdbtNitFrequencySource OBJECT-TYPE
            SYNTAX IsdbtNitRestampingSource
            MAX-ACCESS read-write
            STATUS current
            DESCRIPTION
                "This allows to enable the localization of the frequency using a manual setup."
            ::= { isdbtNitRestampingEntry 7 }

        
        isdbtNitManualFrequency OBJECT-TYPE
            SYNTAX Unsigned32 (0..65535)
            UNITS "1/7 MHz"
            MAX-ACCESS read-write
            STATUS current
            DESCRIPTION
                "This is the first frequency within the list of frequencies from terrestrial delivery system descriptor. Localization is done within each NIT.
                Only valid, if isdbtNitFrequencySource is set to manual(2).
                "
            ::= { isdbtNitRestampingEntry 8 }

        
        isdbtNitVirtualChannelSource OBJECT-TYPE
            SYNTAX IsdbtNitRestampingSource
            MAX-ACCESS read-write
            STATUS current
            DESCRIPTION
                "This allows to enable the localization of the virtual channel using a manual setup."
            ::= { isdbtNitRestampingEntry 9 }

        
        isdbtNitManualVirtualChannel OBJECT-TYPE
            SYNTAX Unsigned32 (0..255)
            MAX-ACCESS read-write
            STATUS current
            DESCRIPTION
                "This indicates the recommended remote control key number to which the TS shall be assigned. This is also known as 'virtual channel'. Localization is done within each NIT.
                Only valid, if isdbtNitVirtualChannelSource is set to manual(2)."
            ::= { isdbtNitRestampingEntry 10 }

        
        isdbtOutput OBJECT IDENTIFIER ::= { rsXx9IsdbtObjects 3 }

        
        isdbtOutTmccTable OBJECT-TYPE
            SYNTAX SEQUENCE OF IsdbtOutTmccEntry
            MAX-ACCESS not-accessible
            STATUS current
            DESCRIPTION
                "TMCC (transmission and multiplexing configuration control)
                current values."
            ::= { isdbtOutput 3 }

        
        isdbtOutTmccEntry OBJECT-TYPE
            SYNTAX IsdbtOutTmccEntry
            MAX-ACCESS not-accessible
            STATUS current
            DESCRIPTION
                "An entry in the isdbtOutTmccTable."
            AUGMENTS { isdbtConfigurationEntry }
            ::= { isdbtOutTmccTable 1 }

        
        IsdbtOutTmccEntry ::=
            SEQUENCE { 
                isdbtOutTmccMode
                    IsdbtMode,
                isdbtOutTmccGuardInterval
                    IsdbtGuardInterval,
                isdbtOutTmccPartialReception
                    TruthValue
             }

        isdbtOutTmccMode OBJECT-TYPE
            SYNTAX IsdbtMode
            MAX-ACCESS read-only
            STATUS current
            DESCRIPTION
                "see textual convention"
            ::= { isdbtOutTmccEntry 2 }

        
        isdbtOutTmccGuardInterval OBJECT-TYPE
            SYNTAX IsdbtGuardInterval
            MAX-ACCESS read-only
            STATUS current
            DESCRIPTION
                "see textual convention"
            ::= { isdbtOutTmccEntry 3 }

        
        isdbtOutTmccPartialReception OBJECT-TYPE
            SYNTAX TruthValue
            MAX-ACCESS read-only
            STATUS current
            DESCRIPTION
                "Description."
            ::= { isdbtOutTmccEntry 4 }

        
        isdbtOutTmccLayerTable OBJECT-TYPE
            SYNTAX SEQUENCE OF IsdbtOutTmccLayerEntry
            MAX-ACCESS not-accessible
            STATUS current
            DESCRIPTION
                "TMCC layer current values."
            ::= { isdbtOutput 4 }

        
        isdbtOutTmccLayerEntry OBJECT-TYPE
            SYNTAX IsdbtOutTmccLayerEntry
            MAX-ACCESS not-accessible
            STATUS current
            DESCRIPTION
                "An entry in the isdbtOutTmccLayerTable."
            AUGMENTS { isdbtTmccLayerEntry }
            ::= { isdbtOutTmccLayerTable 1 }

        
        IsdbtOutTmccLayerEntry ::=
            SEQUENCE { 
                isdbtOutTmccLayerSegments
                    Unsigned32,
                isdbtOutTmccLayerConstellation
                    IsdbtConstellation,
                isdbtOutTmccLayerCodeRate
                    IsdbtCodeRate,
                isdbtOutTmccLayerTimeInterleaver
                    Unsigned32
             }

        isdbtOutTmccLayerSegments OBJECT-TYPE
            SYNTAX Unsigned32
            MAX-ACCESS read-only
            STATUS current
            DESCRIPTION
                "Number of segments manually set for layer."
            ::= { isdbtOutTmccLayerEntry 4 }

        
        isdbtOutTmccLayerConstellation OBJECT-TYPE
            SYNTAX IsdbtConstellation
            MAX-ACCESS read-only
            STATUS current
            DESCRIPTION
                "Description."
            ::= { isdbtOutTmccLayerEntry 5 }

        
        isdbtOutTmccLayerCodeRate OBJECT-TYPE
            SYNTAX IsdbtCodeRate
            MAX-ACCESS read-only
            STATUS current
            DESCRIPTION
                "see textual convention."
            ::= { isdbtOutTmccLayerEntry 6 }

        
        isdbtOutTmccLayerTimeInterleaver OBJECT-TYPE
            SYNTAX Unsigned32
            MAX-ACCESS read-only
            STATUS current
            DESCRIPTION
                "Time interleaver used in layer.
                Value 0 means no interleaving."
            ::= { isdbtOutTmccLayerEntry 7 }

        
        isdbtOutStatusTable OBJECT-TYPE
            SYNTAX SEQUENCE OF IsdbtOutStatusEntry
            MAX-ACCESS not-accessible
            STATUS current
            DESCRIPTION
                "Description."
            ::= { isdbtOutput 5 }

        
        isdbtOutStatusEntry OBJECT-TYPE
            SYNTAX IsdbtOutStatusEntry
            MAX-ACCESS not-accessible
            STATUS current
            DESCRIPTION
                "Description."
            AUGMENTS { isdbtConfigurationEntry }
            ::= { isdbtOutStatusTable 1 }

        
        IsdbtOutStatusEntry ::=
            SEQUENCE { 
                isdbtOutStatusEwbsActFlag
                    INTEGER
             }

        isdbtOutStatusEwbsActFlag OBJECT-TYPE
            SYNTAX INTEGER
                {
                notAvailable(1),
                flagOff(2),
                flagOn(3)
                }
            MAX-ACCESS read-only
            STATUS current
            DESCRIPTION
                "Indicates the status of the transmitted EWBS-Flag (EWBS=Emergency Warning Broadcast System).
                
                notAvailable(1): 'Switch On' information can not be detected in IIP (ISDB-T Information Packet).
                flagOff(2): IIP contains 'Switch On' = Off.
                flagOn(3): IIP contains 'Switch On' = On.
                "
            ::= { isdbtOutStatusEntry 1 }

        
        rsXx9IsdbtConformance OBJECT IDENTIFIER ::= { rsXx9IsdbT 2 }

        
        rsXx9IsdbtCompliances OBJECT IDENTIFIER ::= { rsXx9IsdbtConformance 1 }

        
        isdbtBasicCompliance MODULE-COMPLIANCE
            STATUS current
            DESCRIPTION 
                "The compliance statement for XX9000 ISDB-T exciters."
            MODULE -- this module
                MANDATORY-GROUPS { isdbtObjBasic, isdbtNotifyBasic }
            ::= { rsXx9IsdbtCompliances 1 }

        
        rsXx9IsdbtGroups OBJECT IDENTIFIER ::= { rsXx9IsdbtConformance 2 }

        
        isdbtObjBasic OBJECT-GROUP
            OBJECTS { isdbtStatusNotificationName, isdbtStatusNotificationMask, isdbtStatusNotificationPriority, isdbtStatusNotificationState, isdbtCfgNetworkMode, 
                isdbtCfgCoderSettingsSource, isdbtCfgIipID, isdbtLocalizationEquipmentControl, isdbtLocalizationEquipmentID, isdbtCfgBandwidth, 
                isdbtStTxDelayOffset, isdbtNitManualVirtualChannel, isdbtNitVirtualChannelSource, isdbtNitManualFrequency, isdbtNitFrequencySource, 
                isdbtNitManualAreaCode, isdbtNitAreaCodeSource, isdbtNitTransportManualStreamId, isdbtNitTransportStreamIdSource, isdbtNitManualNetworkId, 
                isdbtNitNetworkIdSource, isdbtOutStatusEwbsActFlag, isdbtTestMode, isdbtTmccNext, isdbtTmccMode, 
                isdbtTmccGuardInterval, isdbtTmccPartialReception, isdbtTmccLayerSegments, isdbtTmccLayerConstellation, isdbtTmccLayerCodeRate, 
                isdbtTmccLayerTimeInterleaver, isdbtOutTmccMode, isdbtOutTmccGuardInterval, isdbtOutTmccPartialReception, isdbtOutTmccLayerSegments, 
                isdbtOutTmccLayerConstellation, isdbtOutTmccLayerCodeRate, isdbtOutTmccLayerTimeInterleaver }
            STATUS current
            DESCRIPTION 
                "Basic objects group."
            ::= { rsXx9IsdbtGroups 1 }

        
        isdbtNotifyBasic NOTIFICATION-GROUP
            NOTIFICATIONS { isdbtIIP, isdbtFrameCounter, isdbtEquipmentId, isdbtManualConfiguration, isdbtActiveConfiguration, 
                isdbtTest }
            STATUS current
            DESCRIPTION 
                "Basic notifications group."
            ::= { rsXx9IsdbtGroups 2 }

        
        isdbtObjObsoleted OBJECT-GROUP
            OBJECTS { isdbtTestGeneration }
            STATUS obsolete
            DESCRIPTION 
                "Description."
            ::= { rsXx9IsdbtGroups 3 }

        
    
    END

--
-- RS-XX9-ISDBT-MIB.mi2
--
