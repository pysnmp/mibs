ACOS-GSLB-STATISTICS-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		gslbStatisticsModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "gslbStatisticsModule OID for ACOS"
				::=  {  acosSchema 422 }

statistics		 OBJECT IDENTIFIER ::= { gslbStatisticsModule 1}

statisticsOperTable OBJECT-TYPE
	 SYNTAX SEQUENCE OF StatisticsOperEntry
	 MAX-ACCESS not-accessible
	 STATUS current
	 DESCRIPTION
		 "GSLB Global stats from object 'gslb.statistics'"
	::= {statistics 2}

statisticsOperEntry OBJECT-TYPE
	SYNTAX StatisticsOperEntry
	MAX-ACCESS not-accessible
	STATUS current
	DESCRIPTION
		"The statisticsOper entry"
	INDEX {
		statisticsOperSlotId
	}
	::= { statisticsOperTable 1 }

StatisticsOperEntry ::=
	SEQUENCE {
		statisticsOperSlotId Integer32,
		statisticsOperCurrSslCtx	 Integer32
	}

statisticsOperSlotId OBJECT-TYPE
	 SYNTAX Integer32
	 MAX-ACCESS read-only
	 STATUS current
	 DESCRIPTION
		 ""
	::= { statisticsOperEntry 1 }

statisticsOperCurrSslCtx OBJECT-TYPE
	 SYNTAX Integer32
	 MAX-ACCESS read-only
	 STATUS current
	 DESCRIPTION
		 "curr-ssl-ctx"
	::= { statisticsOperEntry 2 }

END
