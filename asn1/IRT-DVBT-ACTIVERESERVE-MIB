--
-- IRT-DVBT-ACTIVERESERVE-MIB.my
-- MIB generated by MG-SOFT Visual MIB Builder Version 6.0  Build 88
-- Friday, May 04, 2007 at 16:33:42
--

	IRT-DVBT-ACTIVERESERVE-MIB DEFINITIONS ::= BEGIN
 
		IMPORTS
			eventTimeStamp, eventPriority, eventCounter, mibRelease			
				FROM IRT-COMMONVARBINDS-MIB			
			dvbT, Input1Input2, SelectManualAuto, SelectOnOff, LocalRemote, 
			FaultOK, ReadyNotReady, ExecutedNotExecuted, PresentNotPresent, WarningOK, 
			OkNotOk, MuteOk, SFNMFN			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DateAndTime, DisplayString, TruthValue			
				FROM SNMPv2-TC;
	
	
		-- 1.3.6.1.4.1.19831.1.1.1.2
		dvbActiveReserve MODULE-IDENTITY 
			LAST-UPDATED "200705041400Z"		-- May 04, 2007 at 14:00 GMT
			ORGANIZATION 
				"IRT for WORKING-GROUP-TC-MIB"
			CONTACT-INFO 
				"Contact-info:
				
				Andreas Metz
				
				Institut fuer Rundfunktechnik GmbH
				Broadcast Networks and Servers (SN)
				
				Floriansmuehlstr.60
				80939 Munich
				Germany
				
				Phone: +49 89 32399 325
				Fax: +49 89 32399 354"
			DESCRIPTION 
				"Description:
				
				branch definition
				
				1st level
				
				events               OBJECT IDENTIFIER ::= { dvbActiveReserve 0 }
				dvbARGeneral         OBJECT IDENTIFIER ::= { dvbActiveReserve 1 }
				dvbARAmplifierA      OBJECT IDENTIFIER ::= { dvbActiveReserve 2 }
				dvbARAmplifierB      OBJECT IDENTIFIER ::= { dvbActiveReserve 3 }
				dvbARExciterA        OBJECT IDENTIFIER ::= { dvbActiveReserve 4 }
				dvbARExciterB        OBJECT IDENTIFIER ::= { dvbActiveReserve 5 }
				dvbAREventEnable     OBJECT IDENTIFIER ::= { dvbActiveReserve 6 }
				dvbAREventPriority   OBJECT IDENTIFIER ::= { dvbActiveReserve 7 }
				groups               OBJECT IDENTIFIER ::= { dvbActiveReserve 8 }
				
				2nd level
				
				dvbAREventEnableGeneral     OBJECT IDENTIFIER ::= { dvbAREventEnable 1 }
				dvbAREventEnableAmplifierA  OBJECT IDENTIFIER ::= { dvbAREventEnable 2 }
				dvbAREventEnableAmplifierB  OBJECT IDENTIFIER ::= { dvbAREventEnable 3 }
				dvbAREventEnableExciterA    OBJECT IDENTIFIER ::= { dvbAREventEnable 4 }
				dvbAREventEnableExciterB    OBJECT IDENTIFIER ::= { dvbAREventEnable 5 }
				
				dvbAREventPriorityGeneral     OBJECT IDENTIFIER ::= { dvbAREventPriority 1 }
				dvbAREventPriorityAmplifierA  OBJECT IDENTIFIER ::= { dvbAREventPriority 2 }
				dvbAREventPriorityAmplifierB  OBJECT IDENTIFIER ::= { dvbAREventPriority 3 }
				dvbAREventPriorityExciterA    OBJECT IDENTIFIER ::= { dvbAREventPriority 4 }
				dvbAREventPriorityExciterB    OBJECT IDENTIFIER ::= { dvbAREventPriority 5 }
				
				end branch"
			REVISION "200705041400Z"		-- May 04, 2007 at 14:00 GMT
			DESCRIPTION 
				"change SFNMode,LocalMode (description only) and Module-COMPLIANCE
				change numbering: OIDs 1.3.6.1.4.1.19831.1.1.1.2.7.1.13-19 and 
				1.3.6.1.4.1.19831.1.1.1.2.6.1.13-19!"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dvbT 2 }

		
	
	
--
-- Node definitions
--
	
-- dvb active reserve events
		-- 1.3.6.1.4.1.19831.1.1.1.2.0
		dvbEventsAR OBJECT IDENTIFIER ::= { dvbActiveReserve 0 }

		
		-- 1.3.6.1.4.1.19831.1.1.1.2.0.1
		dvbARInputPreselectionEvent NOTIFICATION-TYPE
			OBJECTS { sysDescr, sysName, sysLocation, eventTimeStamp, eventPriority, 
				eventCounter, dvbARInputPreselection }
			STATUS current
			DESCRIPTION 
				"Description. dvbARInputPreselection notification"
			::= { dvbEventsAR 1 }

		
		-- 1.3.6.1.4.1.19831.1.1.1.2.0.2
		dvbARInputAutomaticEvent NOTIFICATION-TYPE
			OBJECTS { sysDescr, sysName, sysLocation, eventTimeStamp, eventPriority, 
				eventCounter, dvbARInputAutomatic }
			STATUS current
			DESCRIPTION 
				"Description. dvbARInputAutomatic notification"
			::= { dvbEventsAR 2 }

		
		-- 1.3.6.1.4.1.19831.1.1.1.2.0.3
		dvbARPreselectionExciterEvent NOTIFICATION-TYPE
			OBJECTS { sysDescr, sysName, sysLocation, eventTimeStamp, eventPriority, 
				eventCounter, dvbARPreselectionExciter }
			STATUS current
			DESCRIPTION 
				"Description. dvbARPreselectionExciter notification"
			::= { dvbEventsAR 3 }

		
		-- 1.3.6.1.4.1.19831.1.1.1.2.0.4
		dvbARPreselectionAmplifierEvent NOTIFICATION-TYPE
			OBJECTS { sysDescr, sysName, sysLocation, eventTimeStamp, eventPriority, 
				eventCounter, dvbARPreselectionAmplifier }
			STATUS current
			DESCRIPTION 
				"Description. dvbARPreselectionAmplifier notification"
			::= { dvbEventsAR 4 }

		
		-- 1.3.6.1.4.1.19831.1.1.1.2.0.5
		dvbARTransmitterOpModeEvent NOTIFICATION-TYPE
			OBJECTS { sysDescr, sysName, sysLocation, eventTimeStamp, eventPriority, 
				eventCounter, dvbARTransmitterOpMode }
			STATUS current
			DESCRIPTION 
				"Description. dvbARTransmitterOpMode notification"
			::= { dvbEventsAR 5 }

		
		-- 1.3.6.1.4.1.19831.1.1.1.2.0.6
		dvbARReserveControlEvent NOTIFICATION-TYPE
			OBJECTS { sysDescr, sysName, sysLocation, eventTimeStamp, eventPriority, 
				eventCounter, dvbARReserveControl }
			STATUS current
			DESCRIPTION 
				"Description. dvbARReserveControl notification"
			::= { dvbEventsAR 6 }

		
		-- 1.3.6.1.4.1.19831.1.1.1.2.0.7
		dvbARResetFaultEvent NOTIFICATION-TYPE
			OBJECTS { sysDescr, sysName, sysLocation, eventTimeStamp, eventPriority, 
				eventCounter, dvbARResetFault }
			STATUS obsolete
			DESCRIPTION 
				"Notification is inactive!
				
				Description. dvbARResetFault notification"
			::= { dvbEventsAR 7 }

		
		-- 1.3.6.1.4.1.19831.1.1.1.2.0.8
		dvbARActiveAmplifierEvent NOTIFICATION-TYPE
			OBJECTS { sysDescr, sysName, sysLocation, eventTimeStamp, eventPriority, 
				eventCounter, dvbARActiveAmplifier }
			STATUS current
			DESCRIPTION 
				"Description. dvbARActiveAmplifier notification"
			::= { dvbEventsAR 8 }

		
		-- 1.3.6.1.4.1.19831.1.1.1.2.0.9
		dvbARActiveExciterEvent NOTIFICATION-TYPE
			OBJECTS { sysDescr, sysName, sysLocation, eventTimeStamp, eventPriority, 
				eventCounter, dvbARActiveExciter }
			STATUS current
			DESCRIPTION 
				"Description. dvbARActiveExciter notification"
			::= { dvbEventsAR 9 }

		
		-- 1.3.6.1.4.1.19831.1.1.1.2.0.10
		dvbARLocalModeEvent NOTIFICATION-TYPE
			OBJECTS { sysDescr, sysName, sysLocation, eventTimeStamp, eventPriority, 
				eventCounter, dvbARLocalMode }
			STATUS current
			DESCRIPTION 
				"Description. dvbARLocalMode notification"
			::= { dvbEventsAR 10 }

		
		-- 1.3.6.1.4.1.19831.1.1.1.2.0.11
		dvbARControlUnitFaultEvent NOTIFICATION-TYPE
			OBJECTS { sysDescr, sysName, sysLocation, eventTimeStamp, eventPriority, 
				eventCounter, dvbARControlUnitFault }
			STATUS current
			DESCRIPTION 
				"Description. dvbARControlUnitFault notification"
			::= { dvbEventsAR 11 }

		
		-- 1.3.6.1.4.1.19831.1.1.1.2.0.12
		dvbARExciterSwitchOverModeEvent NOTIFICATION-TYPE
			OBJECTS { sysDescr, sysName, sysLocation, eventTimeStamp, eventPriority, 
				eventCounter, dvbARExciterSwitchOverMode }
			STATUS current
			DESCRIPTION 
				"Description. dvbARExciterSwitchOverMode notification"
			::= { dvbEventsAR 12 }

		
		-- 1.3.6.1.4.1.19831.1.1.1.2.0.13
		dvbARExciterSwitchOverReadyEvent NOTIFICATION-TYPE
			OBJECTS { sysDescr, sysName, sysLocation, eventTimeStamp, eventPriority, 
				eventCounter, dvbARAmplifierSwitchOverReady }
			STATUS current
			DESCRIPTION 
				"Description. dvbARExciterSwitchOverReady notification"
			::= { dvbEventsAR 13 }

		
		-- 1.3.6.1.4.1.19831.1.1.1.2.0.14
		dvbARExciterSwitchOverExecutedEvent NOTIFICATION-TYPE
			OBJECTS { sysDescr, sysName, sysLocation, eventTimeStamp, eventPriority, 
				eventCounter, dvbARExciterSwitchOverExecuted }
			STATUS current
			DESCRIPTION 
				"Description. dvbARExciterSwitchOverExecuted notification"
			::= { dvbEventsAR 14 }

		
		-- 1.3.6.1.4.1.19831.1.1.1.2.0.15
		dvbARExciterSwitchOverFaultEvent NOTIFICATION-TYPE
			OBJECTS { sysDescr, sysName, sysLocation, eventTimeStamp, eventPriority, 
				eventCounter, dvbARExciterSwitchOverFault }
			STATUS current
			DESCRIPTION 
				"Description. dvbARExciterSwitchOverFault notification"
			::= { dvbEventsAR 15 }

		
		-- 1.3.6.1.4.1.19831.1.1.1.2.0.16
		dvbARAmplifierSwitchOverModeEvent NOTIFICATION-TYPE
			OBJECTS { sysDescr, sysName, sysLocation, eventTimeStamp, eventPriority, 
				eventCounter, dvbARAmplifierSwitchOverMode }
			STATUS current
			DESCRIPTION 
				"Description. dvbARAmplifierSwitchOverMode notification"
			::= { dvbEventsAR 16 }

		
		-- 1.3.6.1.4.1.19831.1.1.1.2.0.17
		dvbARAmplifierSwitchOverReadyEvent NOTIFICATION-TYPE
			OBJECTS { sysDescr, sysName, sysLocation, eventTimeStamp, eventPriority, 
				eventCounter, dvbARAmplifierSwitchOverReady }
			STATUS current
			DESCRIPTION 
				"Description. dvbARAmplifierSwitchOverReady notification"
			::= { dvbEventsAR 17 }

		
		-- 1.3.6.1.4.1.19831.1.1.1.2.0.18
		dvbARAmplifierSwitchOverExecutedEvent NOTIFICATION-TYPE
			OBJECTS { sysDescr, sysName, sysLocation, eventTimeStamp, eventPriority, 
				eventCounter, dvbARAmplifierSwitchOverExecuted }
			STATUS current
			DESCRIPTION 
				"Description. dvbARAmplifierSwitchOverExecuted notification"
			::= { dvbEventsAR 18 }

		
		-- 1.3.6.1.4.1.19831.1.1.1.2.0.19
		dvbARAmplifierSwitchOverFaultEvent NOTIFICATION-TYPE
			OBJECTS { sysDescr, sysName, sysLocation, eventTimeStamp, eventPriority, 
				eventCounter, dvbARAmplifierSwitchOverFault }
			STATUS current
			DESCRIPTION 
				"Description. dvbARAmplifierSwitchOverFault notification"
			::= { dvbEventsAR 19 }

		
		-- 1.3.6.1.4.1.19831.1.1.1.2.0.20
		dvbARAmplifierARFPresentEvent NOTIFICATION-TYPE
			OBJECTS { sysDescr, sysName, sysLocation, eventTimeStamp, eventPriority, 
				eventCounter, dvbARAmplifierARFPresent }
			STATUS current
			DESCRIPTION 
				"Description. dvbARAmplifierARFPresent notification"
			::= { dvbEventsAR 20 }

		
		-- 1.3.6.1.4.1.19831.1.1.1.2.0.21
		dvbARAmplifierAFaultEvent NOTIFICATION-TYPE
			OBJECTS { sysDescr, sysName, sysLocation, eventTimeStamp, eventPriority, 
				eventCounter, dvbARAmplifierAFault }
			STATUS current
			DESCRIPTION 
				"Description. dvbARAmplifierAFault notification"
			::= { dvbEventsAR 21 }

		
		-- 1.3.6.1.4.1.19831.1.1.1.2.0.22
		dvbARAmplifierAWarningEvent NOTIFICATION-TYPE
			OBJECTS { sysDescr, sysName, sysLocation, eventTimeStamp, eventPriority, 
				eventCounter, dvbARAmplifierAWarning }
			STATUS current
			DESCRIPTION 
				"Description. dvbARAmplifierAWarning notification"
			::= { dvbEventsAR 22 }

		
		-- 1.3.6.1.4.1.19831.1.1.1.2.0.23
		dvbARAmplifierBRFPresentEvent NOTIFICATION-TYPE
			OBJECTS { sysDescr, sysName, sysLocation, eventTimeStamp, eventPriority, 
				eventCounter, dvbARAmplifierBRFPresent }
			STATUS current
			DESCRIPTION 
				"Description. dvbARAmplifierBRFPresent notification"
			::= { dvbEventsAR 23 }

		
		-- 1.3.6.1.4.1.19831.1.1.1.2.0.24
		dvbARAmplifierBFaultEvent NOTIFICATION-TYPE
			OBJECTS { sysDescr, sysName, sysLocation, eventTimeStamp, eventPriority, 
				eventCounter, dvbARAmplifierBFault }
			STATUS current
			DESCRIPTION 
				"Description. dvbARAmplifierBFault notification"
			::= { dvbEventsAR 24 }

		
		-- 1.3.6.1.4.1.19831.1.1.1.2.0.25
		dvbARAmplifierBWarningEvent NOTIFICATION-TYPE
			OBJECTS { sysDescr, sysName, sysLocation, eventTimeStamp, eventPriority, 
				eventCounter, dvbARAmplifierBWarning }
			STATUS current
			DESCRIPTION 
				"Description. dvbARAmplifierBWarning notification"
			::= { dvbEventsAR 25 }

		
		-- 1.3.6.1.4.1.19831.1.1.1.2.0.26
		dvbARExciterAInput1OKEvent NOTIFICATION-TYPE
			OBJECTS { sysDescr, sysName, sysLocation, eventTimeStamp, eventPriority, 
				eventCounter, dvbARExciterAInput1OK }
			STATUS current
			DESCRIPTION 
				"Description. dvbARExciterAInput1OK notification"
			::= { dvbEventsAR 26 }

		
		-- 1.3.6.1.4.1.19831.1.1.1.2.0.27
		dvbARExciterAInput2OKEvent NOTIFICATION-TYPE
			OBJECTS { sysDescr, sysName, sysLocation, eventTimeStamp, eventPriority, 
				eventCounter, dvbARExciterAInput2OK }
			STATUS current
			DESCRIPTION 
				"Description. dvbARExciterAInput2OK notification"
			::= { dvbEventsAR 27 }

		
		-- 1.3.6.1.4.1.19831.1.1.1.2.0.28
		dvbARExciterALocalModeEvent NOTIFICATION-TYPE
			OBJECTS { sysDescr, sysName, sysLocation, eventTimeStamp, eventPriority, 
				eventCounter, dvbARExciterALocalMode }
			STATUS current
			DESCRIPTION 
				"Description. dvbARExciterALocalMode notification"
			::= { dvbEventsAR 28 }

		
		-- 1.3.6.1.4.1.19831.1.1.1.2.0.29
		dvbARExciterAFaultEvent NOTIFICATION-TYPE
			OBJECTS { sysDescr, sysName, sysLocation, eventTimeStamp, eventPriority, 
				eventCounter, dvbARExciterAFault }
			STATUS current
			DESCRIPTION 
				"Description. dvbARExciterAFault notification"
			::= { dvbEventsAR 29 }

		
		-- 1.3.6.1.4.1.19831.1.1.1.2.0.30
		dvbARExciterAWarningEvent NOTIFICATION-TYPE
			OBJECTS { sysDescr, sysName, sysLocation, eventTimeStamp, eventPriority, 
				eventCounter, dvbARExciterAWarning }
			STATUS current
			DESCRIPTION 
				"Description. dvbARExciterAWarning notification"
			::= { dvbEventsAR 30 }

		
		-- 1.3.6.1.4.1.19831.1.1.1.2.0.31
		dvbARExciterAActiveInputEvent NOTIFICATION-TYPE
			OBJECTS { sysDescr, sysName, sysLocation, eventTimeStamp, eventPriority, 
				eventCounter, dvbARExciterAActiveInput }
			STATUS current
			DESCRIPTION 
				"Description. dvbARExciterAActiveInput notification"
			::= { dvbEventsAR 31 }

		
		-- 1.3.6.1.4.1.19831.1.1.1.2.0.32
		dvbARExciterASFNModeEvent NOTIFICATION-TYPE
			OBJECTS { sysDescr, sysName, sysLocation, eventTimeStamp, eventPriority, 
				eventCounter, dvbARExciterASFNMode }
			STATUS current
			DESCRIPTION 
				"Description. dvbARExciterASFNMode notification"
			::= { dvbEventsAR 32 }

		
		-- 1.3.6.1.4.1.19831.1.1.1.2.0.33
		dvbARExciterARefFaultEvent NOTIFICATION-TYPE
			OBJECTS { sysDescr, sysName, sysLocation, eventTimeStamp, eventPriority, 
				eventCounter, dvbARExciterARefFault }
			STATUS current
			DESCRIPTION 
				"Description. dvbARExciterARefFault notification"
			::= { dvbEventsAR 33 }

		
		-- 1.3.6.1.4.1.19831.1.1.1.2.0.34
		dvbARExciterAMuteEvent NOTIFICATION-TYPE
			OBJECTS { sysDescr, sysName, sysLocation, eventTimeStamp, eventPriority, 
				eventCounter, dvbARExciterAMute }
			STATUS current
			DESCRIPTION 
				"Description. dvbARExciterAMute notification"
			::= { dvbEventsAR 34 }

		
		-- 1.3.6.1.4.1.19831.1.1.1.2.0.35
		dvbARExciterAFaultMIPEvent NOTIFICATION-TYPE
			OBJECTS { sysDescr, sysName, sysLocation, eventTimeStamp, eventPriority, 
				eventCounter, dvbARExciterAFaultMIP }
			STATUS current
			DESCRIPTION 
				"Description. dvbARExciterAFaultMIP notification"
			::= { dvbEventsAR 35 }

		
		-- 1.3.6.1.4.1.19831.1.1.1.2.0.36
		dvbARExciterAStuffingModeEvent NOTIFICATION-TYPE
			OBJECTS { sysDescr, sysName, sysLocation, eventTimeStamp, eventPriority, 
				eventCounter, dvbARExciterAStuffingMode }
			STATUS current
			DESCRIPTION 
				"Description. dvbARExciterAStuffingMode notification"
			::= { dvbEventsAR 36 }

		
		-- 1.3.6.1.4.1.19831.1.1.1.2.0.37
		dvbARExciterBInput1OKEvent NOTIFICATION-TYPE
			OBJECTS { sysDescr, sysName, sysLocation, eventTimeStamp, eventPriority, 
				eventCounter, dvbARExciterBInput1OK }
			STATUS current
			DESCRIPTION 
				"Description. dvbARExciterBInput1OK notification"
			::= { dvbEventsAR 37 }

		
		-- 1.3.6.1.4.1.19831.1.1.1.2.0.38
		dvbARExciterBInput2OKEvent NOTIFICATION-TYPE
			OBJECTS { sysDescr, sysName, sysLocation, eventTimeStamp, eventPriority, 
				eventCounter, dvbARExciterBInput2OK }
			STATUS current
			DESCRIPTION 
				"Description. dvbARExciterBInput2OK notification"
			::= { dvbEventsAR 38 }

		
		-- 1.3.6.1.4.1.19831.1.1.1.2.0.39
		dvbARExciterBLocalModeEvent NOTIFICATION-TYPE
			OBJECTS { sysDescr, sysName, sysLocation, eventTimeStamp, eventPriority, 
				eventCounter, dvbARExciterBLocalMode }
			STATUS current
			DESCRIPTION 
				"Description. dvbARExciterBLocalMode  notification"
			::= { dvbEventsAR 39 }

		
		-- 1.3.6.1.4.1.19831.1.1.1.2.0.40
		dvbARExciterBFaultEvent NOTIFICATION-TYPE
			OBJECTS { sysDescr, sysName, sysLocation, eventTimeStamp, eventPriority, 
				eventCounter, dvbARExciterBFault }
			STATUS current
			DESCRIPTION 
				"Description. dvbARExciterBFault notification"
			::= { dvbEventsAR 40 }

		
		-- 1.3.6.1.4.1.19831.1.1.1.2.0.41
		dvbARExciterBWarningEvent NOTIFICATION-TYPE
			OBJECTS { sysDescr, sysName, sysLocation, eventTimeStamp, eventPriority, 
				eventCounter, dvbARExciterBWarning }
			STATUS current
			DESCRIPTION 
				"Description. dvbARExciterBWarning notification"
			::= { dvbEventsAR 41 }

		
		-- 1.3.6.1.4.1.19831.1.1.1.2.0.42
		dvbARExciterBActiveInputEvent NOTIFICATION-TYPE
			OBJECTS { sysDescr, sysName, sysLocation, eventTimeStamp, eventPriority, 
				eventCounter, dvbARExciterBActiveInput }
			STATUS current
			DESCRIPTION 
				"Description. dvbARExciterBActiveInput notification"
			::= { dvbEventsAR 42 }

		
		-- 1.3.6.1.4.1.19831.1.1.1.2.0.43
		dvbARExciterBSFNModeEvent NOTIFICATION-TYPE
			OBJECTS { sysDescr, sysName, sysLocation, eventTimeStamp, eventPriority, 
				eventCounter, dvbARExciterBSFNMode }
			STATUS current
			DESCRIPTION 
				"Description. dvbARExciterBSFNMode notification"
			::= { dvbEventsAR 43 }

		
		-- 1.3.6.1.4.1.19831.1.1.1.2.0.44
		dvbARExciterBRefFaultEvent NOTIFICATION-TYPE
			OBJECTS { sysDescr, sysName, sysLocation, eventTimeStamp, eventPriority, 
				eventCounter, dvbARExciterBRefFault }
			STATUS current
			DESCRIPTION 
				"Description. dvbARExciterBRefFault notification"
			::= { dvbEventsAR 44 }

		
		-- 1.3.6.1.4.1.19831.1.1.1.2.0.45
		dvbARExciterBMuteEvent NOTIFICATION-TYPE
			OBJECTS { sysDescr, sysName, sysLocation, eventTimeStamp, eventPriority, 
				eventCounter, dvbARExciterBMute }
			STATUS current
			DESCRIPTION 
				"Description. dvbARExciterBMute notification"
			::= { dvbEventsAR 45 }

		
		-- 1.3.6.1.4.1.19831.1.1.1.2.0.46
		dvbARExciterBFaultMIPEvent NOTIFICATION-TYPE
			OBJECTS { sysDescr, sysName, sysLocation, eventTimeStamp, eventPriority, 
				eventCounter, dvbARExciterBFaultMIP }
			STATUS current
			DESCRIPTION 
				"Description. dvbARExciterBFaultMIPEvent notification"
			::= { dvbEventsAR 46 }

		
		-- 1.3.6.1.4.1.19831.1.1.1.2.0.47
		dvbARExciterBStuffingModeEvent NOTIFICATION-TYPE
			OBJECTS { sysDescr, sysName, sysLocation, eventTimeStamp, eventPriority, 
				eventCounter, dvbARExciterBStuffingMode }
			STATUS current
			DESCRIPTION 
				"Description. dvbARExciterBStuffingMode notification"
			::= { dvbEventsAR 47 }

		
-- dvb active reserve general
		-- 1.3.6.1.4.1.19831.1.1.1.2.1
		dvbARGeneral OBJECT IDENTIFIER ::= { dvbActiveReserve 1 }

		
		-- 1.3.6.1.4.1.19831.1.1.1.2.1.1
		dvbARInputPreselection OBJECT-TYPE
			SYNTAX Input1Input2
			MAX-ACCESS read-write
			STATUS current
			DESCRIPTION
				"Preselection input of aktive reserve 
				
				(0) undefined
				(1) Input 1
				(2) Input 2"
			::= { dvbARGeneral 1 }

		
		-- 1.3.6.1.4.1.19831.1.1.1.2.1.2
		dvbARInputAutomatic OBJECT-TYPE
			SYNTAX SelectManualAuto
			MAX-ACCESS read-write
			STATUS current
			DESCRIPTION
				"Input selection mode of aktive reserve: manual or automatic
				
				
				(0) undefined
				(1) manual 
				(2) automatic"
			::= { dvbARGeneral 2 }

		
		-- 1.3.6.1.4.1.19831.1.1.1.2.1.3
		dvbARPreselectionExciter OBJECT-TYPE
			SYNTAX INTEGER
				{
				undefined(0),
				exciterA(1),
				exciterB(2)
				}
			MAX-ACCESS read-write
			STATUS current
			DESCRIPTION
				"Aktive reserve. Preselection of the exciter
				
				"
			::= { dvbARGeneral 3 }

		
		-- 1.3.6.1.4.1.19831.1.1.1.2.1.4
		dvbARPreselectionAmplifier OBJECT-TYPE
			SYNTAX INTEGER
				{
				undefined(0),
				amplifierA(1),
				amplifierB(2),
				amplifierAB(3),
				amplifierABtodummyload(4)
				}
			MAX-ACCESS read-write
			STATUS current
			DESCRIPTION
				"Aktive reserve. Preselection amplifier 
				
				"
			::= { dvbARGeneral 4 }

		
		-- 1.3.6.1.4.1.19831.1.1.1.2.1.5
		dvbARTransmitterOpMode OBJECT-TYPE
			SYNTAX SelectOnOff
			MAX-ACCESS read-write
			STATUS current
			DESCRIPTION
				"General transmitter control of aktive reserve
				
				(0) undefined
				(1) ON
				(2) OFF"
			::= { dvbARGeneral 5 }

		
		-- 1.3.6.1.4.1.19831.1.1.1.2.1.6
		dvbARReserveControl OBJECT-TYPE
			SYNTAX SelectOnOff
			MAX-ACCESS read-write
			STATUS current
			DESCRIPTION
				"Reserve control of aktive reserve
				
				(0) undefined
				(1) ON 
				(2) OFF "
			::= { dvbARGeneral 6 }

		
		-- 1.3.6.1.4.1.19831.1.1.1.2.1.7
		dvbARResetFault OBJECT-TYPE
			SYNTAX Unsigned32
			MAX-ACCESS read-write
			STATUS obsolete
			DESCRIPTION
				"Description. Massage is inactive!
				
				Tigger for reset the sum fault
				
				<1>
				
				(1) reset sum fault"
			::= { dvbARGeneral 7 }

		
		-- 1.3.6.1.4.1.19831.1.1.1.2.1.8
		dvbARActiveAmplifier OBJECT-TYPE
			SYNTAX INTEGER
				{
				undefined(0),
				amplifierA(1),
				amplifierB(2),
				amplifierAB(3),
				amplifierABtoDummyload(4)
				}
			MAX-ACCESS read-only
			STATUS current
			DESCRIPTION
				"Active amplifier  of aktive reserve
				
				"
			::= { dvbARGeneral 8 }

		
		-- 1.3.6.1.4.1.19831.1.1.1.2.1.9
		dvbARActiveExciter OBJECT-TYPE
			SYNTAX INTEGER
				{
				undefined(0),
				exciterA(1),
				exciterB(2)
				}
			MAX-ACCESS read-only
			STATUS current
			DESCRIPTION
				"Active exciter of aktive reserve
				
				
				"
			::= { dvbARGeneral 9 }

		
		-- 1.3.6.1.4.1.19831.1.1.1.2.1.10
		dvbARLocalMode OBJECT-TYPE
			SYNTAX LocalRemote
			MAX-ACCESS read-only
			STATUS current
			DESCRIPTION
				"Active reserve. Local mode
				
				(0) undefined
				(1) local
				(2) remote"
			::= { dvbARGeneral 10 }

		
		-- 1.3.6.1.4.1.19831.1.1.1.2.1.11
		dvbARControlUnitFault OBJECT-TYPE
			SYNTAX FaultOK
			UNITS " "
			MAX-ACCESS read-only
			STATUS current
			DESCRIPTION
				"Aktive reserve. State of the control unit
				
				(0) undefined
				(1) fault
				(2) ok"
			::= { dvbARGeneral 11 }

		
		-- 1.3.6.1.4.1.19831.1.1.1.2.1.12
		dvbARExciterSwitchOverMode OBJECT-TYPE
			SYNTAX SelectManualAuto
			MAX-ACCESS read-write
			STATUS current
			DESCRIPTION
				"Aktive reserve. Exciter switch over mode: manual or automatic
				
				(0) undefined
				(1) manual 
				(2) automatic"
			::= { dvbARGeneral 12 }

		
		-- 1.3.6.1.4.1.19831.1.1.1.2.1.13
		dvbARExciterSwitchOverReady OBJECT-TYPE
			SYNTAX ReadyNotReady
			MAX-ACCESS read-only
			STATUS current
			DESCRIPTION
				"Aktive reserve. State of the exciter switch over unit
				
				(0) undefined
				(1) ready
				(2) not ready"
			::= { dvbARGeneral 13 }

		
		-- 1.3.6.1.4.1.19831.1.1.1.2.1.14
		dvbARExciterSwitchOverExecuted OBJECT-TYPE
			SYNTAX ExecutedNotExecuted
			MAX-ACCESS read-only
			STATUS current
			DESCRIPTION
				"Aktive reserve. Shows if the exciter switch over unit it has executed
				
				(0) undefined
				(1) executed
				(2) not executed"
			::= { dvbARGeneral 14 }

		
		-- 1.3.6.1.4.1.19831.1.1.1.2.1.15
		dvbARExciterSwitchOverFault OBJECT-TYPE
			SYNTAX FaultOK
			MAX-ACCESS read-only
			STATUS current
			DESCRIPTION
				"Aktive reserve. Fault state of the exciter switch over unit
				
				(0) undefined
				(1) faulty
				(2) ok"
			::= { dvbARGeneral 15 }

		
		-- 1.3.6.1.4.1.19831.1.1.1.2.1.16
		dvbARAmplifierSwitchOverMode OBJECT-TYPE
			SYNTAX SelectManualAuto
			MAX-ACCESS read-write
			STATUS current
			DESCRIPTION
				"Active reserve. Amplifier switch over mode: manual or automatic
				
				(0) undefined
				(1) manual
				(2) automatic"
			::= { dvbARGeneral 16 }

		
		-- 1.3.6.1.4.1.19831.1.1.1.2.1.17
		dvbARAmplifierSwitchOverReady OBJECT-TYPE
			SYNTAX ReadyNotReady
			MAX-ACCESS read-only
			STATUS current
			DESCRIPTION
				"Active reserve. State of the amplifier switch over unit
				
				(0) undefined
				(1) ready
				(2) not ready"
			::= { dvbARGeneral 17 }

		
		-- 1.3.6.1.4.1.19831.1.1.1.2.1.18
		dvbARAmplifierSwitchOverExecuted OBJECT-TYPE
			SYNTAX ExecutedNotExecuted
			MAX-ACCESS read-only
			STATUS current
			DESCRIPTION
				"Active reserve. Shows if the amplifier switch over unit it has executed
				
				(0) undefined
				(1) executed
				(2) not executed"
			::= { dvbARGeneral 18 }

		
		-- 1.3.6.1.4.1.19831.1.1.1.2.1.19
		dvbARAmplifierSwitchOverFault OBJECT-TYPE
			SYNTAX FaultOK
			MAX-ACCESS read-only
			STATUS current
			DESCRIPTION
				"Active reserve. Fault state of the amplifier switch over unit
				
				(0) undefined
				(1) faulty
				(2) ok"
			::= { dvbARGeneral 19 }

		
-- dvb active reserve amplifier A
		-- 1.3.6.1.4.1.19831.1.1.1.2.2
		dvbARAmplifierA OBJECT IDENTIFIER ::= { dvbActiveReserve 2 }

		
		-- 1.3.6.1.4.1.19831.1.1.1.2.2.1
		dvbARAmplifierARFPresent OBJECT-TYPE
			SYNTAX PresentNotPresent
			MAX-ACCESS read-only
			STATUS current
			DESCRIPTION
				"Active reserve. Describes if the output power of the amplifier A is present
				
				(0) undefined
				(1) present
				(2) not present"
			::= { dvbARAmplifierA 1 }

		
		-- 1.3.6.1.4.1.19831.1.1.1.2.2.2
		dvbARAmplifierAFault OBJECT-TYPE
			SYNTAX FaultOK
			MAX-ACCESS read-only
			STATUS current
			DESCRIPTION
				"Active reserve. Fault state of amplifier A
				
				(0) undefined
				(1) fault
				(2) ok"
			::= { dvbARAmplifierA 2 }

		
		-- 1.3.6.1.4.1.19831.1.1.1.2.2.3
		dvbARAmplifierAWarning OBJECT-TYPE
			SYNTAX WarningOK
			MAX-ACCESS read-only
			STATUS current
			DESCRIPTION
				"Active reserve. Warning state of amplifier A
				
				(0) undefined
				(1) warning
				(2) ok"
			::= { dvbARAmplifierA 3 }

		
-- dvb active reserve amplifier B
		-- 1.3.6.1.4.1.19831.1.1.1.2.3
		dvbARAmplifierB OBJECT IDENTIFIER ::= { dvbActiveReserve 3 }

		
		-- 1.3.6.1.4.1.19831.1.1.1.2.3.1
		dvbARAmplifierBRFPresent OBJECT-TYPE
			SYNTAX PresentNotPresent
			MAX-ACCESS read-only
			STATUS current
			DESCRIPTION
				"Active reserve. Describes if the output power of the amplifier B is present
				
				(0) undefined
				(1) present
				(2) not present"
			::= { dvbARAmplifierB 1 }

		
		-- 1.3.6.1.4.1.19831.1.1.1.2.3.2
		dvbARAmplifierBFault OBJECT-TYPE
			SYNTAX FaultOK
			MAX-ACCESS read-only
			STATUS current
			DESCRIPTION
				"Active reserve. Fault state of amplifier B
				
				(0) undefined
				(1) fault
				(2) ok"
			::= { dvbARAmplifierB 2 }

		
		-- 1.3.6.1.4.1.19831.1.1.1.2.3.3
		dvbARAmplifierBWarning OBJECT-TYPE
			SYNTAX WarningOK
			MAX-ACCESS read-only
			STATUS current
			DESCRIPTION
				"Active reserve. Warning state of amplifier B
				
				(0) undefined
				(1) warning
				(2) ok"
			::= { dvbARAmplifierB 3 }

		
-- dvb active reserve excister A
		-- 1.3.6.1.4.1.19831.1.1.1.2.4
		dvbARExciterA OBJECT IDENTIFIER ::= { dvbActiveReserve 4 }

		
		-- 1.3.6.1.4.1.19831.1.1.1.2.4.1
		dvbARExciterAInput1OK OBJECT-TYPE
			SYNTAX OkNotOk
			MAX-ACCESS read-only
			STATUS current
			DESCRIPTION
				"Active reserve. Describes if the input signal at the input 1 of exiter A is ok
				
				(0) undefined
				(1) signal ok
				(2) signal is not ok"
			::= { dvbARExciterA 1 }

		
		-- 1.3.6.1.4.1.19831.1.1.1.2.4.2
		dvbARExciterAInput2OK OBJECT-TYPE
			SYNTAX OkNotOk
			MAX-ACCESS read-only
			STATUS current
			DESCRIPTION
				"Active reserve. Describes if the input signal at the input 2 of exiter A is ok
				
				(0) undefined
				(1) signal ok
				(2) signal is not ok"
			::= { dvbARExciterA 2 }

		
		-- 1.3.6.1.4.1.19831.1.1.1.2.4.3
		dvbARExciterALocalMode OBJECT-TYPE
			SYNTAX LocalRemote
			MAX-ACCESS read-only
			STATUS current
			DESCRIPTION
				"Active reserve. State of the local mode of exciter A
				
				(0) undefined
				(1) local
				(2) remote"
			::= { dvbARExciterA 3 }

		
		-- 1.3.6.1.4.1.19831.1.1.1.2.4.4
		dvbARExciterAFault OBJECT-TYPE
			SYNTAX FaultOK
			MAX-ACCESS read-only
			STATUS current
			DESCRIPTION
				"Active reserve. State of the exciter A
				
				(0) undefined
				(1) fault
				(2) ok"
			::= { dvbARExciterA 4 }

		
		-- 1.3.6.1.4.1.19831.1.1.1.2.4.5
		dvbARExciterAWarning OBJECT-TYPE
			SYNTAX WarningOK
			MAX-ACCESS read-only
			STATUS current
			DESCRIPTION
				"Active reserve. Warning state of the exciter A
				
				(0) undefined
				(1) warning
				(2) ok"
			::= { dvbARExciterA 5 }

		
		-- 1.3.6.1.4.1.19831.1.1.1.2.4.6
		dvbARExciterAActiveInput OBJECT-TYPE
			SYNTAX INTEGER
				{
				ndefined(0),
				input1(1),
				input2(2),
				seamless(3),
				hmHierarchicalModulation(4)
				}
			MAX-ACCESS read-only
			STATUS current
			DESCRIPTION
				"Active reserve. Active input of the exciter A 
				
				"
			::= { dvbARExciterA 6 }

		
		-- 1.3.6.1.4.1.19831.1.1.1.2.4.7
		dvbARExciterASFNMode OBJECT-TYPE
			SYNTAX SFNMFN
			MAX-ACCESS read-only
			STATUS current
			DESCRIPTION
				"Active reserve. SFN mode of exciter A
				
				(0) undefined
				(1) SFN
				(2) MFN"
			::= { dvbARExciterA 7 }

		
		-- 1.3.6.1.4.1.19831.1.1.1.2.4.8
		dvbARExciterARefFault OBJECT-TYPE
			SYNTAX FaultOK
			MAX-ACCESS read-only
			STATUS current
			DESCRIPTION
				"Active reserve. Fault state of the GPS input or the reference frequency of exciter A
				
				(0) undefined
				(1) fault
				(2) ok"
			::= { dvbARExciterA 8 }

		
		-- 1.3.6.1.4.1.19831.1.1.1.2.4.9
		dvbARExciterAMute OBJECT-TYPE
			SYNTAX MuteOk
			MAX-ACCESS read-only
			STATUS current
			DESCRIPTION
				"Active reserve. Mute state of exciter A
				
				(0) undefined
				(1) mute
				(2) ok"
			::= { dvbARExciterA 9 }

		
		-- 1.3.6.1.4.1.19831.1.1.1.2.4.10
		dvbARExciterAFaultMIP OBJECT-TYPE
			SYNTAX FaultOK
			MAX-ACCESS read-only
			STATUS current
			DESCRIPTION
				"Active reserve. MIP fault state of exciter A
				
				(0) undefined
				(1) fault
				(2) ok"
			::= { dvbARExciterA 10 }

		
		-- 1.3.6.1.4.1.19831.1.1.1.2.4.11
		dvbARExciterAStuffingMode OBJECT-TYPE
			SYNTAX SelectOnOff
			MAX-ACCESS read-only
			STATUS current
			DESCRIPTION
				"Active reserve. Stuffing state of exciter A
				
				(0) undefined
				(1) ON 
				(2) OFF "
			::= { dvbARExciterA 11 }

		
-- dvb active reserve exciter B
		-- 1.3.6.1.4.1.19831.1.1.1.2.5
		dvbARExciterB OBJECT IDENTIFIER ::= { dvbActiveReserve 5 }

		
		-- 1.3.6.1.4.1.19831.1.1.1.2.5.1
		dvbARExciterBInput1OK OBJECT-TYPE
			SYNTAX OkNotOk
			MAX-ACCESS read-only
			STATUS current
			DESCRIPTION
				"Active reserve. Describes if the input signal at the input 1 of exciter B is ok
				
				(0) undefined
				(1) signal ok
				(2) signal is not ok "
			::= { dvbARExciterB 1 }

		
		-- 1.3.6.1.4.1.19831.1.1.1.2.5.2
		dvbARExciterBInput2OK OBJECT-TYPE
			SYNTAX OkNotOk
			MAX-ACCESS read-only
			STATUS current
			DESCRIPTION
				"Active reserve. Describes if the input signal at the input 2 of exciter B is ok
				
				(0) undefined
				(1) signal ok
				(2) signal is not ok "
			::= { dvbARExciterB 2 }

		
		-- 1.3.6.1.4.1.19831.1.1.1.2.5.3
		dvbARExciterBLocalMode OBJECT-TYPE
			SYNTAX LocalRemote
			MAX-ACCESS read-only
			STATUS current
			DESCRIPTION
				"Active reserve. State of the local mode of exciter B
				
				(0) undefined
				(1) local
				(2) remote"
			::= { dvbARExciterB 3 }

		
		-- 1.3.6.1.4.1.19831.1.1.1.2.5.4
		dvbARExciterBFault OBJECT-TYPE
			SYNTAX FaultOK
			MAX-ACCESS read-only
			STATUS current
			DESCRIPTION
				"Active reserve. Fault state of the exciter B
				
				(0) undefined
				(1) fault
				(2) ok"
			::= { dvbARExciterB 4 }

		
		-- 1.3.6.1.4.1.19831.1.1.1.2.5.5
		dvbARExciterBWarning OBJECT-TYPE
			SYNTAX WarningOK
			MAX-ACCESS read-only
			STATUS current
			DESCRIPTION
				"Active reserve. Warning state of the exciter B
				
				(0) undefined
				(1) warning
				(2) ok"
			::= { dvbARExciterB 5 }

		
		-- 1.3.6.1.4.1.19831.1.1.1.2.5.6
		dvbARExciterBActiveInput OBJECT-TYPE
			SYNTAX INTEGER
				{
				undefined(0),
				input1(1),
				input2(2),
				seamless(3),
				hmHierarchicalModulation(4)
				}
			MAX-ACCESS read-only
			STATUS current
			DESCRIPTION
				"Active reserve. Active input of the exciter B 
				
				"
			::= { dvbARExciterB 6 }

		
		-- 1.3.6.1.4.1.19831.1.1.1.2.5.7
		dvbARExciterBSFNMode OBJECT-TYPE
			SYNTAX SFNMFN
			MAX-ACCESS read-only
			STATUS current
			DESCRIPTION
				"Active reserve. SFN mode of exciter B
				
				(0) undefined
				(1) SFN
				(2) MFN"
			::= { dvbARExciterB 7 }

		
		-- 1.3.6.1.4.1.19831.1.1.1.2.5.8
		dvbARExciterBMute OBJECT-TYPE
			SYNTAX MuteOk
			MAX-ACCESS read-only
			STATUS current
			DESCRIPTION
				"Active reserve. Mute state of exciter B
				
				(0) undefined
				(1) mute
				(2) ok"
			::= { dvbARExciterB 8 }

		
		-- 1.3.6.1.4.1.19831.1.1.1.2.5.9
		dvbARExciterBRefFault OBJECT-TYPE
			SYNTAX FaultOK
			MAX-ACCESS read-only
			STATUS current
			DESCRIPTION
				"Active reserve. Fault state of the GPS input or the reference frequency of exciter B
				
				(0) undefined
				(1) fault
				(2) ok"
			::= { dvbARExciterB 9 }

		
		-- 1.3.6.1.4.1.19831.1.1.1.2.5.10
		dvbARExciterBFaultMIP OBJECT-TYPE
			SYNTAX FaultOK
			MAX-ACCESS read-only
			STATUS current
			DESCRIPTION
				"Active reserve. MIP fault state of exciter B
				
				(0) undefined
				(1) fault
				(2) ok"
			::= { dvbARExciterB 10 }

		
		-- 1.3.6.1.4.1.19831.1.1.1.2.5.11
		dvbARExciterBStuffingMode OBJECT-TYPE
			SYNTAX SelectOnOff
			MAX-ACCESS read-only
			STATUS current
			DESCRIPTION
				"Active reserve. Stuffing state of exciter B
				
				(0) undefined
				(1) ON 
				(2) OFF "
			::= { dvbARExciterB 11 }

		
-- dvb active reserve event enable
		-- 1.3.6.1.4.1.19831.1.1.1.2.6
		dvbAREventEnable OBJECT IDENTIFIER ::= { dvbActiveReserve 6 }

		
-- dvb active reserve general:  switch for Event
		-- 1.3.6.1.4.1.19831.1.1.1.2.6.1
		dvbAREventEnableGeneral OBJECT IDENTIFIER ::= { dvbAREventEnable 1 }

		
		-- 1.3.6.1.4.1.19831.1.1.1.2.6.1.1
		dvbARInputPreselectionEnable OBJECT-TYPE
			SYNTAX TruthValue
			MAX-ACCESS read-write
			STATUS current
			DESCRIPTION
				"Description.Enable/Disable switch for dvbARInputPreselection event"
			::= { dvbAREventEnableGeneral 1 }

		
		-- 1.3.6.1.4.1.19831.1.1.1.2.6.1.2
		dvbARInputAutomaticEnable OBJECT-TYPE
			SYNTAX TruthValue
			MAX-ACCESS read-write
			STATUS current
			DESCRIPTION
				"Description.Enable/Disable switch for dvbARInputAutomatic event"
			::= { dvbAREventEnableGeneral 2 }

		
		-- 1.3.6.1.4.1.19831.1.1.1.2.6.1.3
		dvbARPreselectionExciterEnable OBJECT-TYPE
			SYNTAX TruthValue
			MAX-ACCESS read-write
			STATUS current
			DESCRIPTION
				"Description.Enable/Disable switch for dvbARPreselectionExciter event"
			::= { dvbAREventEnableGeneral 3 }

		
		-- 1.3.6.1.4.1.19831.1.1.1.2.6.1.4
		dvbARPreselectionAmplifierEnable OBJECT-TYPE
			SYNTAX TruthValue
			MAX-ACCESS read-write
			STATUS current
			DESCRIPTION
				"Description.Enable/Disable switch for dvbARPreselectionAmplifier event"
			::= { dvbAREventEnableGeneral 4 }

		
		-- 1.3.6.1.4.1.19831.1.1.1.2.6.1.5
		dvbARTransmitterOpModeEnable OBJECT-TYPE
			SYNTAX TruthValue
			MAX-ACCESS read-write
			STATUS current
			DESCRIPTION
				"Description.Enable/Disable switch for dvbARTransmitterOpMode event"
			::= { dvbAREventEnableGeneral 5 }

		
		-- 1.3.6.1.4.1.19831.1.1.1.2.6.1.6
		dvbARReserveControlEnable OBJECT-TYPE
			SYNTAX TruthValue
			MAX-ACCESS read-write
			STATUS current
			DESCRIPTION
				"Description.Enable/Disable switch for dvbARReserveControl event"
			::= { dvbAREventEnableGeneral 6 }

		
		-- 1.3.6.1.4.1.19831.1.1.1.2.6.1.7
		dvbARResetFaultEnable OBJECT-TYPE
			SYNTAX TruthValue
			MAX-ACCESS read-write
			STATUS obsolete
			DESCRIPTION
				"Massage ist inctive!
				
				Description. Enable/Disable switch for dvbARResetFault event"
			::= { dvbAREventEnableGeneral 7 }

		
		-- 1.3.6.1.4.1.19831.1.1.1.2.6.1.8
		dvbARActiveAmplifierEnable OBJECT-TYPE
			SYNTAX TruthValue
			MAX-ACCESS read-write
			STATUS current
			DESCRIPTION
				"Description.Enable/Disable switch for dvbARActiveAmplifier event"
			::= { dvbAREventEnableGeneral 8 }

		
		-- 1.3.6.1.4.1.19831.1.1.1.2.6.1.9
		dvbARActiveExciterEnable OBJECT-TYPE
			SYNTAX TruthValue
			MAX-ACCESS read-write
			STATUS current
			DESCRIPTION
				"Description.Enable/Disable switch for dvbARActiveExciter event"
			::= { dvbAREventEnableGeneral 9 }

		
		-- 1.3.6.1.4.1.19831.1.1.1.2.6.1.10
		dvbARLocalModeEnable OBJECT-TYPE
			SYNTAX TruthValue
			MAX-ACCESS read-write
			STATUS current
			DESCRIPTION
				"Description.Enable/Disable switch for dvbARLocalMode event"
			::= { dvbAREventEnableGeneral 10 }

		
		-- 1.3.6.1.4.1.19831.1.1.1.2.6.1.11
		dvbARControlUnitFaultEnable OBJECT-TYPE
			SYNTAX TruthValue
			MAX-ACCESS read-write
			STATUS current
			DESCRIPTION
				"Description.Enable/Disable switch for dvbARControlUnitFault event"
			::= { dvbAREventEnableGeneral 11 }

		
		-- 1.3.6.1.4.1.19831.1.1.1.2.6.1.12
		dvbARExciterSwitchOverModeEnable OBJECT-TYPE
			SYNTAX TruthValue
			MAX-ACCESS read-write
			STATUS current
			DESCRIPTION
				"Description.Enable/Disable switch for dvbARExciterSwitchOverMode event"
			::= { dvbAREventEnableGeneral 12 }

		
		-- 1.3.6.1.4.1.19831.1.1.1.2.6.1.13
		dvbARExciterSwitchOverReadyEnable OBJECT-TYPE
			SYNTAX TruthValue
			MAX-ACCESS read-write
			STATUS current
			DESCRIPTION
				"Description.Enable/Disable switch for dvbARExciterSwitchOverReady event"
			::= { dvbAREventEnableGeneral 13 }

		
		-- 1.3.6.1.4.1.19831.1.1.1.2.6.1.14
		dvbARExciterSwitchOverExecutedEnable OBJECT-TYPE
			SYNTAX TruthValue
			MAX-ACCESS read-write
			STATUS current
			DESCRIPTION
				"Description.Enable/Disable switch for dvbARExciterSwitchOverExecuted event"
			::= { dvbAREventEnableGeneral 14 }

		
		-- 1.3.6.1.4.1.19831.1.1.1.2.6.1.15
		dvbARExciterSwitchOverFaultEnable OBJECT-TYPE
			SYNTAX TruthValue
			MAX-ACCESS read-write
			STATUS current
			DESCRIPTION
				"Description.Enable/Disable switch for dvbARExciterSwitchOverFault event"
			::= { dvbAREventEnableGeneral 15 }

		
		-- 1.3.6.1.4.1.19831.1.1.1.2.6.1.16
		dvbARAmplifierSwitchOverModeEnable OBJECT-TYPE
			SYNTAX TruthValue
			MAX-ACCESS read-write
			STATUS current
			DESCRIPTION
				"Description.Enable/Disable switch for dvbARAmplifierSwitchOverMode event"
			::= { dvbAREventEnableGeneral 16 }

		
		-- 1.3.6.1.4.1.19831.1.1.1.2.6.1.17
		dvbARAmplifierSwitchOverReadyEnable OBJECT-TYPE
			SYNTAX TruthValue
			MAX-ACCESS read-write
			STATUS current
			DESCRIPTION
				"Description.Enable/Disable switch for dvbARAmplifierSwitchOverReady event"
			::= { dvbAREventEnableGeneral 17 }

		
		-- 1.3.6.1.4.1.19831.1.1.1.2.6.1.18
		dvbARAmplifierSwitchOverExecutedEnable OBJECT-TYPE
			SYNTAX TruthValue
			MAX-ACCESS read-write
			STATUS current
			DESCRIPTION
				"Description.Enable/Disable switch for  dvbARAmplifierSwitchOverExecuted event"
			::= { dvbAREventEnableGeneral 18 }

		
		-- 1.3.6.1.4.1.19831.1.1.1.2.6.1.19
		dvbARAmplifierSwitchOverFaultEnable OBJECT-TYPE
			SYNTAX TruthValue
			MAX-ACCESS read-write
			STATUS current
			DESCRIPTION
				"Description.Enable/Disable switch for dvbARAmplifierSwitchOverFault event"
			::= { dvbAREventEnableGeneral 19 }

		
-- dvb active reserve amplifier A:  switch for Event
		-- 1.3.6.1.4.1.19831.1.1.1.2.6.2
		dvbAREventEnableAmplifierA OBJECT IDENTIFIER ::= { dvbAREventEnable 2 }

		
		-- 1.3.6.1.4.1.19831.1.1.1.2.6.2.1
		dvbARAmplifierARFPresentEnable OBJECT-TYPE
			SYNTAX TruthValue
			MAX-ACCESS read-write
			STATUS current
			DESCRIPTION
				"Description.Enable/Disable switch for dvbARAmplifierARFPresent event"
			::= { dvbAREventEnableAmplifierA 1 }

		
		-- 1.3.6.1.4.1.19831.1.1.1.2.6.2.2
		dvbARAmplifierAFaultEnable OBJECT-TYPE
			SYNTAX TruthValue
			MAX-ACCESS read-write
			STATUS current
			DESCRIPTION
				"Description.Enable/Disable switch for dvbARAmplifierAFault event"
			::= { dvbAREventEnableAmplifierA 2 }

		
		-- 1.3.6.1.4.1.19831.1.1.1.2.6.2.3
		dvbARAmplifierAWarningEnable OBJECT-TYPE
			SYNTAX TruthValue
			MAX-ACCESS read-write
			STATUS current
			DESCRIPTION
				"Description.Enable/Disable switch for dvbARAmplifierAWarning event"
			::= { dvbAREventEnableAmplifierA 3 }

		
-- dvb active reserve amplifier B:  switch for Event
		-- 1.3.6.1.4.1.19831.1.1.1.2.6.3
		dvbAREventEnableAmplifierB OBJECT IDENTIFIER ::= { dvbAREventEnable 3 }

		
		-- 1.3.6.1.4.1.19831.1.1.1.2.6.3.1
		dvbARAmplifierBRFPresentEnable OBJECT-TYPE
			SYNTAX TruthValue
			MAX-ACCESS read-write
			STATUS current
			DESCRIPTION
				"Description.Enable/Disable switch for dvbARAmplifierBRFPresent event"
			::= { dvbAREventEnableAmplifierB 1 }

		
		-- 1.3.6.1.4.1.19831.1.1.1.2.6.3.2
		dvbARAmplifierBFaultEnable OBJECT-TYPE
			SYNTAX TruthValue
			MAX-ACCESS read-write
			STATUS current
			DESCRIPTION
				"Description.Enable/Disable switch for dvbARAmplifierBFault event"
			::= { dvbAREventEnableAmplifierB 2 }

		
		-- 1.3.6.1.4.1.19831.1.1.1.2.6.3.3
		dvbARAmplifierBWarningEnable OBJECT-TYPE
			SYNTAX TruthValue
			MAX-ACCESS read-write
			STATUS current
			DESCRIPTION
				"Description.Enable/Disable switch for dvbARAmplifierBWarning event"
			::= { dvbAREventEnableAmplifierB 3 }

		
-- dvb active reserve exciter A:  switch for event
		-- 1.3.6.1.4.1.19831.1.1.1.2.6.4
		dvbAREventEnableExciterA OBJECT IDENTIFIER ::= { dvbAREventEnable 4 }

		
		-- 1.3.6.1.4.1.19831.1.1.1.2.6.4.1
		dvbARExciterAInput1OKEnable OBJECT-TYPE
			SYNTAX TruthValue
			MAX-ACCESS read-write
			STATUS current
			DESCRIPTION
				"Description.Enable/Disable switch for dvbARExciterAInput1OK event"
			::= { dvbAREventEnableExciterA 1 }

		
		-- 1.3.6.1.4.1.19831.1.1.1.2.6.4.2
		dvbARExciterAInput2OKEnable OBJECT-TYPE
			SYNTAX TruthValue
			MAX-ACCESS read-write
			STATUS current
			DESCRIPTION
				"Description.Enable/Disable switch for dvbARExciterAInput2OK event"
			::= { dvbAREventEnableExciterA 2 }

		
		-- 1.3.6.1.4.1.19831.1.1.1.2.6.4.3
		dvbARExciterALocalModeEnable OBJECT-TYPE
			SYNTAX TruthValue
			MAX-ACCESS read-write
			STATUS current
			DESCRIPTION
				"Description.Enable/Disable switch for dvbARExciterALocalMode event"
			::= { dvbAREventEnableExciterA 3 }

		
		-- 1.3.6.1.4.1.19831.1.1.1.2.6.4.4
		dvbARExciterAFaultEnable OBJECT-TYPE
			SYNTAX TruthValue
			MAX-ACCESS read-write
			STATUS current
			DESCRIPTION
				"Description.Enable/Disable switch for dvbARExciterAFault event"
			::= { dvbAREventEnableExciterA 4 }

		
		-- 1.3.6.1.4.1.19831.1.1.1.2.6.4.5
		dvbARExciterAWarningEnable OBJECT-TYPE
			SYNTAX TruthValue
			MAX-ACCESS read-write
			STATUS current
			DESCRIPTION
				"Description.Enable/Disable switch for dvbARExciterAWarning event"
			::= { dvbAREventEnableExciterA 5 }

		
		-- 1.3.6.1.4.1.19831.1.1.1.2.6.4.6
		dvbARExciterAActiveInputEnable OBJECT-TYPE
			SYNTAX TruthValue
			MAX-ACCESS read-write
			STATUS current
			DESCRIPTION
				"Description.Enable/Disable switch for dvbARExciterAActiveInput event"
			::= { dvbAREventEnableExciterA 6 }

		
		-- 1.3.6.1.4.1.19831.1.1.1.2.6.4.7
		dvbARExciterASFNModeEnable OBJECT-TYPE
			SYNTAX TruthValue
			MAX-ACCESS read-write
			STATUS current
			DESCRIPTION
				"Description.Enable/Disable switch for dvbARExciterASFNMode event"
			::= { dvbAREventEnableExciterA 7 }

		
		-- 1.3.6.1.4.1.19831.1.1.1.2.6.4.8
		dvbARExciterARefFaultEnable OBJECT-TYPE
			SYNTAX TruthValue
			MAX-ACCESS read-write
			STATUS current
			DESCRIPTION
				"Description.Enable/Disable switch for dvbARExciterARefFault event"
			::= { dvbAREventEnableExciterA 8 }

		
		-- 1.3.6.1.4.1.19831.1.1.1.2.6.4.9
		dvbARExciterAMuteEnable OBJECT-TYPE
			SYNTAX TruthValue
			MAX-ACCESS read-write
			STATUS current
			DESCRIPTION
				"Description.Enable/Disable switch for dvbARExciterAMute event"
			::= { dvbAREventEnableExciterA 9 }

		
		-- 1.3.6.1.4.1.19831.1.1.1.2.6.4.10
		dvbARExciterAFaultMIPEnable OBJECT-TYPE
			SYNTAX TruthValue
			MAX-ACCESS read-write
			STATUS current
			DESCRIPTION
				"Description.Enable/Disable switch for dvbARExciterAFaultMIP event"
			::= { dvbAREventEnableExciterA 10 }

		
		-- 1.3.6.1.4.1.19831.1.1.1.2.6.4.11
		dvbARExciterAStuffingModeEnable OBJECT-TYPE
			SYNTAX TruthValue
			MAX-ACCESS read-write
			STATUS current
			DESCRIPTION
				"Description.Enable/Disable switch for dvbARExciterAStuffingMode event"
			::= { dvbAREventEnableExciterA 11 }

		
-- dvb active reserve exciter B: switch event
		-- 1.3.6.1.4.1.19831.1.1.1.2.6.5
		dvbAREventEnableExciterB OBJECT IDENTIFIER ::= { dvbAREventEnable 5 }

		
		-- 1.3.6.1.4.1.19831.1.1.1.2.6.5.1
		dvbARExciterBInput1OKEnable OBJECT-TYPE
			SYNTAX TruthValue
			MAX-ACCESS read-write
			STATUS current
			DESCRIPTION
				"Description.Enable/Disable switch for dvbARExciterBInput1OK event"
			::= { dvbAREventEnableExciterB 1 }

		
		-- 1.3.6.1.4.1.19831.1.1.1.2.6.5.2
		dvbARExciterBInput2OKEnable OBJECT-TYPE
			SYNTAX TruthValue
			MAX-ACCESS read-write
			STATUS current
			DESCRIPTION
				"Description.Enable/Disable switch for dvbARExciterBInput2OK event"
			::= { dvbAREventEnableExciterB 2 }

		
		-- 1.3.6.1.4.1.19831.1.1.1.2.6.5.3
		dvbARExciterBLocalModeEnable OBJECT-TYPE
			SYNTAX TruthValue
			MAX-ACCESS read-write
			STATUS current
			DESCRIPTION
				"Description.Enable/Disable switch for dvbARExciterBLocalMode event"
			::= { dvbAREventEnableExciterB 3 }

		
		-- 1.3.6.1.4.1.19831.1.1.1.2.6.5.4
		dvbARExciterBFaultEnable OBJECT-TYPE
			SYNTAX TruthValue
			MAX-ACCESS read-write
			STATUS current
			DESCRIPTION
				"Description.Enable/Disable switch for dvbARExciterBFault event"
			::= { dvbAREventEnableExciterB 4 }

		
		-- 1.3.6.1.4.1.19831.1.1.1.2.6.5.5
		dvbARExciterBWarningEnable OBJECT-TYPE
			SYNTAX TruthValue
			MAX-ACCESS read-write
			STATUS current
			DESCRIPTION
				"Description.Enable/Disable switch for dvbARExciterBWarning event"
			::= { dvbAREventEnableExciterB 5 }

		
		-- 1.3.6.1.4.1.19831.1.1.1.2.6.5.6
		dvbARExciterBActiveInputEnable OBJECT-TYPE
			SYNTAX TruthValue
			MAX-ACCESS read-write
			STATUS current
			DESCRIPTION
				"Description.Enable/Disable switch for dvbARExciterBActiveInput event"
			::= { dvbAREventEnableExciterB 6 }

		
		-- 1.3.6.1.4.1.19831.1.1.1.2.6.5.7
		dvbARExciterBSFNModeEnable OBJECT-TYPE
			SYNTAX TruthValue
			MAX-ACCESS read-write
			STATUS current
			DESCRIPTION
				"Description.Enable/Disable switch for dvbARExciterBSFNMode event"
			::= { dvbAREventEnableExciterB 7 }

		
		-- 1.3.6.1.4.1.19831.1.1.1.2.6.5.8
		dvbARExciterBMuteEnable OBJECT-TYPE
			SYNTAX TruthValue
			MAX-ACCESS read-write
			STATUS current
			DESCRIPTION
				"Description.Enable/Disable switch for dvbARExciterBMute event"
			::= { dvbAREventEnableExciterB 8 }

		
		-- 1.3.6.1.4.1.19831.1.1.1.2.6.5.9
		dvbARExciterBRefFaultEnable OBJECT-TYPE
			SYNTAX TruthValue
			MAX-ACCESS read-write
			STATUS current
			DESCRIPTION
				"Description.Enable/Disable switch for dvbARExciterBRefFault event"
			::= { dvbAREventEnableExciterB 9 }

		
		-- 1.3.6.1.4.1.19831.1.1.1.2.6.5.10
		dvbARExciterBFaultMIPEnable OBJECT-TYPE
			SYNTAX TruthValue
			MAX-ACCESS read-write
			STATUS current
			DESCRIPTION
				"Description.Enable/Disable switch for dvbARExciterBFaultMIP event"
			::= { dvbAREventEnableExciterB 10 }

		
		-- 1.3.6.1.4.1.19831.1.1.1.2.6.5.11
		dvbARExciterBStuffingModeEnable OBJECT-TYPE
			SYNTAX TruthValue
			MAX-ACCESS read-write
			STATUS current
			DESCRIPTION
				"Description.Enable/Disable switch for dvbARExciterBStuffingMode event"
			::= { dvbAREventEnableExciterB 11 }

		
-- dvb active reserve event priority
		-- 1.3.6.1.4.1.19831.1.1.1.2.7
		dvbAREventPriority OBJECT IDENTIFIER ::= { dvbActiveReserve 7 }

		
-- dvb active reserve event priority general
		-- 1.3.6.1.4.1.19831.1.1.1.2.7.1
		dvbAREventPriorityGeneral OBJECT IDENTIFIER ::= { dvbAREventPriority 1 }

		
		-- 1.3.6.1.4.1.19831.1.1.1.2.7.1.1
		dvbARInputPreselectionPriority OBJECT-TYPE
			SYNTAX Unsigned32
			MAX-ACCESS read-write
			STATUS current
			DESCRIPTION
				"Description.Priority for dvbARInputPreselection event"
			::= { dvbAREventPriorityGeneral 1 }

		
		-- 1.3.6.1.4.1.19831.1.1.1.2.7.1.2
		dvbARInputAutomaticPriority OBJECT-TYPE
			SYNTAX Unsigned32
			MAX-ACCESS read-write
			STATUS current
			DESCRIPTION
				"Description.Priority for dvbARInputAutomatic event"
			::= { dvbAREventPriorityGeneral 2 }

		
		-- 1.3.6.1.4.1.19831.1.1.1.2.7.1.3
		dvbARPreselectionExciterPriority OBJECT-TYPE
			SYNTAX Unsigned32
			MAX-ACCESS read-write
			STATUS current
			DESCRIPTION
				"Description.Priority for dvbARPreselectionExciter event"
			::= { dvbAREventPriorityGeneral 3 }

		
		-- 1.3.6.1.4.1.19831.1.1.1.2.7.1.4
		dvbARPreselectionAmplifierPriority OBJECT-TYPE
			SYNTAX Unsigned32
			MAX-ACCESS read-write
			STATUS current
			DESCRIPTION
				"Description.Priority for dvbARPreselectionAmplifier event"
			::= { dvbAREventPriorityGeneral 4 }

		
		-- 1.3.6.1.4.1.19831.1.1.1.2.7.1.5
		dvbARTransmitterOpModePriority OBJECT-TYPE
			SYNTAX Unsigned32
			MAX-ACCESS read-write
			STATUS current
			DESCRIPTION
				"Description.Priority for dvbARTransmitterOpMode event"
			::= { dvbAREventPriorityGeneral 5 }

		
		-- 1.3.6.1.4.1.19831.1.1.1.2.7.1.6
		dvbARReserveControlPriority OBJECT-TYPE
			SYNTAX Unsigned32
			MAX-ACCESS read-write
			STATUS current
			DESCRIPTION
				"Description.Priority for dvbARReserveControl event"
			::= { dvbAREventPriorityGeneral 6 }

		
		-- 1.3.6.1.4.1.19831.1.1.1.2.7.1.7
		dvbARResetFaultPriority OBJECT-TYPE
			SYNTAX Unsigned32
			MAX-ACCESS read-write
			STATUS obsolete
			DESCRIPTION
				"Massage ist inactive!
				
				Description. Enable/Disable switch for dvbARResetFault event"
			::= { dvbAREventPriorityGeneral 7 }

		
		-- 1.3.6.1.4.1.19831.1.1.1.2.7.1.8
		dvbARActiveAmplifierPriority OBJECT-TYPE
			SYNTAX Unsigned32
			MAX-ACCESS read-write
			STATUS current
			DESCRIPTION
				"Description.Priority for dvbARActiveAmplifier event"
			::= { dvbAREventPriorityGeneral 8 }

		
		-- 1.3.6.1.4.1.19831.1.1.1.2.7.1.9
		dvbARActiveExciterPriority OBJECT-TYPE
			SYNTAX Unsigned32
			MAX-ACCESS read-write
			STATUS current
			DESCRIPTION
				"Description.Priority for dvbARActiveExciter event"
			::= { dvbAREventPriorityGeneral 9 }

		
		-- 1.3.6.1.4.1.19831.1.1.1.2.7.1.10
		dvbARLocalModePriority OBJECT-TYPE
			SYNTAX Unsigned32
			MAX-ACCESS read-write
			STATUS current
			DESCRIPTION
				"Description.Priority for dvbARLocalMode event"
			::= { dvbAREventPriorityGeneral 10 }

		
		-- 1.3.6.1.4.1.19831.1.1.1.2.7.1.11
		dvbARControlUnitFaultPriority OBJECT-TYPE
			SYNTAX Unsigned32
			MAX-ACCESS read-write
			STATUS current
			DESCRIPTION
				"Description.Priority for dvbARControlUnitFault event"
			::= { dvbAREventPriorityGeneral 11 }

		
		-- 1.3.6.1.4.1.19831.1.1.1.2.7.1.12
		dvbARExciterSwitchOverModePriority OBJECT-TYPE
			SYNTAX Unsigned32
			MAX-ACCESS read-write
			STATUS current
			DESCRIPTION
				"Description.Priority for dvbARExciterSwitchOverMode event"
			::= { dvbAREventPriorityGeneral 12 }

		
		-- 1.3.6.1.4.1.19831.1.1.1.2.7.1.13
		dvbARExciterSwitchOverReadyPriority OBJECT-TYPE
			SYNTAX Unsigned32
			MAX-ACCESS read-write
			STATUS current
			DESCRIPTION
				"Description.Priority for dvbARExciterSwitchOverReady event"
			::= { dvbAREventPriorityGeneral 13 }

		
		-- 1.3.6.1.4.1.19831.1.1.1.2.7.1.14
		dvbARExciterSwitchOverExecutedPriority OBJECT-TYPE
			SYNTAX Unsigned32
			MAX-ACCESS read-write
			STATUS current
			DESCRIPTION
				"Description.Priority for dvbARExciterSwitchOverExecuted event"
			::= { dvbAREventPriorityGeneral 14 }

		
		-- 1.3.6.1.4.1.19831.1.1.1.2.7.1.15
		dvbARExciterSwitchOverFaultPriority OBJECT-TYPE
			SYNTAX Unsigned32
			MAX-ACCESS read-write
			STATUS current
			DESCRIPTION
				"Description.Priority for dvbARExciterSwitchOverFault event"
			::= { dvbAREventPriorityGeneral 15 }

		
		-- 1.3.6.1.4.1.19831.1.1.1.2.7.1.16
		dvbARAmplifierSwitchOverModePriority OBJECT-TYPE
			SYNTAX Unsigned32
			MAX-ACCESS read-write
			STATUS current
			DESCRIPTION
				"Description.Priority for dvbARAmplifierSwitchOverMode event"
			::= { dvbAREventPriorityGeneral 16 }

		
		-- 1.3.6.1.4.1.19831.1.1.1.2.7.1.17
		dvbARAmplifierSwitchOverReadyPriority OBJECT-TYPE
			SYNTAX Unsigned32
			MAX-ACCESS read-write
			STATUS current
			DESCRIPTION
				"Description.Priority for dvbARAmplifierSwitchOverReady event"
			::= { dvbAREventPriorityGeneral 17 }

		
		-- 1.3.6.1.4.1.19831.1.1.1.2.7.1.18
		dvbARAmplifierSwitchOverExecutedPriority OBJECT-TYPE
			SYNTAX Unsigned32
			MAX-ACCESS read-write
			STATUS current
			DESCRIPTION
				"Description.Priority for dvbARAmplifierSwitchOverExecuted event"
			::= { dvbAREventPriorityGeneral 18 }

		
		-- 1.3.6.1.4.1.19831.1.1.1.2.7.1.19
		dvbARAmplifierSwitchOverFaultPriority OBJECT-TYPE
			SYNTAX Unsigned32
			MAX-ACCESS read-write
			STATUS current
			DESCRIPTION
				"Description.Priority for dvbARAmplifierSwitchOverFault event"
			::= { dvbAREventPriorityGeneral 19 }

		
-- dvb active reserve  event priority amplifier A
		-- 1.3.6.1.4.1.19831.1.1.1.2.7.2
		dvbAREventPriorityAmplifierA OBJECT IDENTIFIER ::= { dvbAREventPriority 2 }

		
		-- 1.3.6.1.4.1.19831.1.1.1.2.7.2.1
		dvbARAmplifierARFPresentPriority OBJECT-TYPE
			SYNTAX Unsigned32
			MAX-ACCESS read-write
			STATUS current
			DESCRIPTION
				"Description.Priority for dvbARAmplifierARFPresent event"
			::= { dvbAREventPriorityAmplifierA 1 }

		
		-- 1.3.6.1.4.1.19831.1.1.1.2.7.2.2
		dvbARAmplifierAFaultPriority OBJECT-TYPE
			SYNTAX Unsigned32
			MAX-ACCESS read-write
			STATUS current
			DESCRIPTION
				"Description.Priority for dvbARAmplifierAFault event"
			::= { dvbAREventPriorityAmplifierA 2 }

		
		-- 1.3.6.1.4.1.19831.1.1.1.2.7.2.3
		dvbARAmplifierAWarningPriority OBJECT-TYPE
			SYNTAX Unsigned32
			MAX-ACCESS read-write
			STATUS current
			DESCRIPTION
				"Description.Priority for dvbARAmplifierAWarning event"
			::= { dvbAREventPriorityAmplifierA 3 }

		
-- dvb active reserve event priority amplifier B
		-- 1.3.6.1.4.1.19831.1.1.1.2.7.3
		dvbAREventPriorityAmplifierB OBJECT IDENTIFIER ::= { dvbAREventPriority 3 }

		
		-- 1.3.6.1.4.1.19831.1.1.1.2.7.3.1
		dvbARAmplifierBRFPresentPriority OBJECT-TYPE
			SYNTAX Unsigned32
			MAX-ACCESS read-write
			STATUS current
			DESCRIPTION
				"Description.Priority for dvbARAmplifierBRFPresent event"
			::= { dvbAREventPriorityAmplifierB 1 }

		
		-- 1.3.6.1.4.1.19831.1.1.1.2.7.3.2
		dvbARAmplifierBFaultPriority OBJECT-TYPE
			SYNTAX Unsigned32
			MAX-ACCESS read-write
			STATUS current
			DESCRIPTION
				"Description.Priority for dvbARAmplifierBFault event"
			::= { dvbAREventPriorityAmplifierB 2 }

		
		-- 1.3.6.1.4.1.19831.1.1.1.2.7.3.3
		dvbARAmplifierBWarningPriority OBJECT-TYPE
			SYNTAX Unsigned32
			MAX-ACCESS read-write
			STATUS current
			DESCRIPTION
				"Description.Priority for dvbARAmplifierBWarning event"
			::= { dvbAREventPriorityAmplifierB 3 }

		
-- dvb active reserve event priority exciter A
		-- 1.3.6.1.4.1.19831.1.1.1.2.7.4
		dvbAREventPriorityExciterA OBJECT IDENTIFIER ::= { dvbAREventPriority 4 }

		
		-- 1.3.6.1.4.1.19831.1.1.1.2.7.4.1
		dvbARExciterAInput1OKPriority OBJECT-TYPE
			SYNTAX Unsigned32
			MAX-ACCESS read-write
			STATUS current
			DESCRIPTION
				"Description.Priority for dvbARExciterAInput1OK event"
			::= { dvbAREventPriorityExciterA 1 }

		
		-- 1.3.6.1.4.1.19831.1.1.1.2.7.4.2
		dvbARExciterAInput2OKPriority OBJECT-TYPE
			SYNTAX Unsigned32
			MAX-ACCESS read-write
			STATUS current
			DESCRIPTION
				"Description.Priority for dvbARExciterAInput2OK event"
			::= { dvbAREventPriorityExciterA 2 }

		
		-- 1.3.6.1.4.1.19831.1.1.1.2.7.4.3
		dvbARExciterALocalModePriority OBJECT-TYPE
			SYNTAX Unsigned32
			MAX-ACCESS read-write
			STATUS current
			DESCRIPTION
				"Description.Priority for dvbARExciterALocalMode event"
			::= { dvbAREventPriorityExciterA 3 }

		
		-- 1.3.6.1.4.1.19831.1.1.1.2.7.4.4
		dvbARExciterAFaultPriority OBJECT-TYPE
			SYNTAX Unsigned32
			MAX-ACCESS read-write
			STATUS current
			DESCRIPTION
				"Description.Priority for dvbARExciterAFault event"
			::= { dvbAREventPriorityExciterA 4 }

		
		-- 1.3.6.1.4.1.19831.1.1.1.2.7.4.5
		dvbARExciterAWarningPriority OBJECT-TYPE
			SYNTAX Unsigned32
			MAX-ACCESS read-write
			STATUS current
			DESCRIPTION
				"Description.Priority for dvbARExciterAWarning event"
			::= { dvbAREventPriorityExciterA 5 }

		
		-- 1.3.6.1.4.1.19831.1.1.1.2.7.4.6
		dvbARExciterAActiveInputPriority OBJECT-TYPE
			SYNTAX Unsigned32
			MAX-ACCESS read-write
			STATUS current
			DESCRIPTION
				"Description.Priority for dvbARExciterAActiveInput event"
			::= { dvbAREventPriorityExciterA 6 }

		
		-- 1.3.6.1.4.1.19831.1.1.1.2.7.4.7
		dvbARExciterASFNModePriority OBJECT-TYPE
			SYNTAX Unsigned32
			MAX-ACCESS read-write
			STATUS current
			DESCRIPTION
				"Description.Priority for dvbARExciterASFNMode event"
			::= { dvbAREventPriorityExciterA 7 }

		
		-- 1.3.6.1.4.1.19831.1.1.1.2.7.4.8
		dvbARExciterARefFaultPriority OBJECT-TYPE
			SYNTAX Unsigned32
			MAX-ACCESS read-write
			STATUS current
			DESCRIPTION
				"Description.Priority for Event dvbARExciterARefFault event"
			::= { dvbAREventPriorityExciterA 8 }

		
		-- 1.3.6.1.4.1.19831.1.1.1.2.7.4.9
		dvbARExciterAMutePriority OBJECT-TYPE
			SYNTAX Unsigned32
			MAX-ACCESS read-write
			STATUS current
			DESCRIPTION
				"Description.Priority for dvbARExciterAMute event"
			::= { dvbAREventPriorityExciterA 9 }

		
		-- 1.3.6.1.4.1.19831.1.1.1.2.7.4.10
		dvbARExciterAFaultMIPPriority OBJECT-TYPE
			SYNTAX Unsigned32
			MAX-ACCESS read-write
			STATUS current
			DESCRIPTION
				"Description.Priority for dvbARExciterAFaultMIP event"
			::= { dvbAREventPriorityExciterA 10 }

		
		-- 1.3.6.1.4.1.19831.1.1.1.2.7.4.11
		dvbARExciterAStuffingModePriority OBJECT-TYPE
			SYNTAX Unsigned32
			MAX-ACCESS read-write
			STATUS current
			DESCRIPTION
				"Description.Priority for dvbARExciterAStuffingMode event"
			::= { dvbAREventPriorityExciterA 11 }

		
-- dvb active reserve event priority exciter B
		-- 1.3.6.1.4.1.19831.1.1.1.2.7.5
		dvbAREventPriorityExciterB OBJECT IDENTIFIER ::= { dvbAREventPriority 5 }

		
		-- 1.3.6.1.4.1.19831.1.1.1.2.7.5.1
		dvbARExciterBInput1OKPriority OBJECT-TYPE
			SYNTAX Unsigned32
			MAX-ACCESS read-write
			STATUS current
			DESCRIPTION
				"Description.Priority for dvbARExciterBInput1OK event"
			::= { dvbAREventPriorityExciterB 1 }

		
		-- 1.3.6.1.4.1.19831.1.1.1.2.7.5.2
		dvbARExciterBInput2OKPriority OBJECT-TYPE
			SYNTAX Unsigned32
			MAX-ACCESS read-write
			STATUS current
			DESCRIPTION
				"Description.Priority for dvbARExciterBInput2OK event"
			::= { dvbAREventPriorityExciterB 2 }

		
		-- 1.3.6.1.4.1.19831.1.1.1.2.7.5.3
		dvbARExciterBLocalModePriority OBJECT-TYPE
			SYNTAX Unsigned32
			MAX-ACCESS read-write
			STATUS current
			DESCRIPTION
				"Description.Priority for dvbARExciterBLocalMode event"
			::= { dvbAREventPriorityExciterB 3 }

		
		-- 1.3.6.1.4.1.19831.1.1.1.2.7.5.4
		dvbARExciterBFaultPriority OBJECT-TYPE
			SYNTAX Unsigned32
			MAX-ACCESS read-write
			STATUS current
			DESCRIPTION
				"Description.Priority for dvbARExciterBFault event"
			::= { dvbAREventPriorityExciterB 4 }

		
		-- 1.3.6.1.4.1.19831.1.1.1.2.7.5.5
		dvbARExciterBWarningPriority OBJECT-TYPE
			SYNTAX Unsigned32
			MAX-ACCESS read-write
			STATUS current
			DESCRIPTION
				"Description.Priority for dvbARExciterBWarning event"
			::= { dvbAREventPriorityExciterB 5 }

		
		-- 1.3.6.1.4.1.19831.1.1.1.2.7.5.6
		dvbARExciterBActiveInputPriority OBJECT-TYPE
			SYNTAX Unsigned32
			MAX-ACCESS read-write
			STATUS current
			DESCRIPTION
				"Description.Priority for dvbARExciterBActiveInput event"
			::= { dvbAREventPriorityExciterB 6 }

		
		-- 1.3.6.1.4.1.19831.1.1.1.2.7.5.7
		dvbARExciterBSFNModePriority OBJECT-TYPE
			SYNTAX Unsigned32
			MAX-ACCESS read-write
			STATUS current
			DESCRIPTION
				"Description.Priority for dvbARExciterBSFNMode event"
			::= { dvbAREventPriorityExciterB 7 }

		
		-- 1.3.6.1.4.1.19831.1.1.1.2.7.5.8
		dvbARExciterBMutePriority OBJECT-TYPE
			SYNTAX Unsigned32
			MAX-ACCESS read-write
			STATUS current
			DESCRIPTION
				"Description.Priority for dvbARExciterBMute event"
			::= { dvbAREventPriorityExciterB 8 }

		
		-- 1.3.6.1.4.1.19831.1.1.1.2.7.5.9
		dvbARExciterBRefFaultPriority OBJECT-TYPE
			SYNTAX Unsigned32
			MAX-ACCESS read-write
			STATUS current
			DESCRIPTION
				"Description.Priority for dvbARExciterBRefFault event"
			::= { dvbAREventPriorityExciterB 9 }

		
		-- 1.3.6.1.4.1.19831.1.1.1.2.7.5.10
		dvbARExciterBFaultMIPPriority OBJECT-TYPE
			SYNTAX Unsigned32
			MAX-ACCESS read-write
			STATUS current
			DESCRIPTION
				"Description.Priority for dvbARExciterBFaultMIP event"
			::= { dvbAREventPriorityExciterB 10 }

		
		-- 1.3.6.1.4.1.19831.1.1.1.2.7.5.11
		dvbARExciterBStuffingModePriority OBJECT-TYPE
			SYNTAX Unsigned32
			MAX-ACCESS read-write
			STATUS current
			DESCRIPTION
				"Description.Priority for dvbARExciterBStuffingMode event"
			::= { dvbAREventPriorityExciterB 11 }

		
		-- 1.3.6.1.4.1.19831.1.1.1.2.8
		groupsAR OBJECT IDENTIFIER ::= { dvbActiveReserve 8 }

		
		-- 1.3.6.1.4.1.19831.1.1.1.2.8.1
		objectGroupAR OBJECT-GROUP
			OBJECTS { dvbARInputPreselection, dvbARInputAutomatic, dvbARPreselectionExciter, dvbARPreselectionAmplifier, dvbARTransmitterOpMode, 
				dvbARReserveControl, dvbARActiveAmplifier, dvbARActiveExciter, dvbARLocalMode, dvbARControlUnitFault, 
				dvbARExciterSwitchOverMode, dvbARExciterSwitchOverReady, dvbARExciterSwitchOverExecuted, dvbARExciterSwitchOverFault, dvbARAmplifierSwitchOverMode, 
				dvbARAmplifierSwitchOverReady, dvbARAmplifierSwitchOverExecuted, dvbARAmplifierSwitchOverFault, dvbARAmplifierARFPresent, dvbARAmplifierAFault, 
				dvbARAmplifierAWarning, dvbARAmplifierBRFPresent, dvbARAmplifierBFault, dvbARAmplifierBWarning, dvbARExciterAInput1OK, 
				dvbARExciterAInput2OK, dvbARExciterALocalMode, dvbARExciterAFault, dvbARExciterAWarning, dvbARExciterAActiveInput, 
				dvbARExciterASFNMode, dvbARExciterARefFault, dvbARExciterAMute, dvbARExciterAFaultMIP, dvbARExciterAStuffingMode, 
				dvbARExciterBInput1OK, dvbARExciterBInput2OK, dvbARExciterBLocalMode, dvbARExciterBFault, dvbARExciterBWarning, 
				dvbARExciterBActiveInput, dvbARExciterBSFNMode, dvbARExciterBMute, dvbARExciterBRefFault, dvbARExciterBFaultMIP, 
				dvbARExciterBStuffingMode, dvbARInputPreselectionEnable, dvbARInputAutomaticEnable, dvbARPreselectionExciterEnable, dvbARPreselectionAmplifierEnable, 
				dvbARTransmitterOpModeEnable, dvbARReserveControlEnable, dvbARActiveAmplifierEnable, dvbARActiveExciterEnable, dvbARLocalModeEnable, 
				dvbARControlUnitFaultEnable, dvbARExciterSwitchOverModeEnable, dvbARExciterSwitchOverExecutedEnable, dvbARExciterSwitchOverFaultEnable, dvbARAmplifierSwitchOverModeEnable, 
				dvbARAmplifierSwitchOverReadyEnable, dvbARAmplifierSwitchOverExecutedEnable, dvbARAmplifierSwitchOverFaultEnable, dvbARExciterSwitchOverReadyEnable, dvbARAmplifierARFPresentEnable, 
				dvbARAmplifierAFaultEnable, dvbARAmplifierAWarningEnable, dvbARAmplifierBRFPresentEnable, dvbARAmplifierBFaultEnable, dvbARAmplifierBWarningEnable, 
				dvbARExciterAInput1OKEnable, dvbARExciterAInput2OKEnable, dvbARExciterALocalModeEnable, dvbARExciterAFaultEnable, dvbARExciterAWarningEnable, 
				dvbARExciterAActiveInputEnable, dvbARExciterASFNModeEnable, dvbARExciterARefFaultEnable, dvbARExciterAMuteEnable, dvbARExciterAFaultMIPEnable, 
				dvbARExciterAStuffingModeEnable, dvbARExciterBInput1OKEnable, dvbARExciterBInput2OKEnable, dvbARExciterBLocalModeEnable, dvbARExciterBFaultEnable, 
				dvbARExciterBWarningEnable, dvbARExciterBActiveInputEnable, dvbARExciterBSFNModeEnable, dvbARExciterBMuteEnable, dvbARExciterBRefFaultEnable, 
				dvbARExciterBFaultMIPEnable, dvbARExciterBStuffingModeEnable, dvbARInputPreselectionPriority, dvbARInputAutomaticPriority, dvbARPreselectionExciterPriority, 
				dvbARPreselectionAmplifierPriority, dvbARTransmitterOpModePriority, dvbARReserveControlPriority, dvbARActiveAmplifierPriority, dvbARActiveExciterPriority, 
				dvbARLocalModePriority, dvbARControlUnitFaultPriority, dvbARExciterSwitchOverModePriority, dvbARExciterSwitchOverExecutedPriority, dvbARExciterSwitchOverFaultPriority, 
				dvbARAmplifierSwitchOverModePriority, dvbARAmplifierSwitchOverReadyPriority, dvbARAmplifierSwitchOverExecutedPriority, dvbARAmplifierSwitchOverFaultPriority, dvbARExciterSwitchOverReadyPriority, 
				dvbARAmplifierARFPresentPriority, dvbARAmplifierAFaultPriority, dvbARAmplifierAWarningPriority, dvbARAmplifierBRFPresentPriority, dvbARAmplifierBFaultPriority, 
				dvbARAmplifierBWarningPriority, dvbARExciterAInput1OKPriority, dvbARExciterAInput2OKPriority, dvbARExciterALocalModePriority, dvbARExciterAFaultPriority, 
				dvbARExciterAWarningPriority, dvbARExciterAActiveInputPriority, dvbARExciterASFNModePriority, dvbARExciterARefFaultPriority, dvbARExciterAMutePriority, 
				dvbARExciterAFaultMIPPriority, dvbARExciterAStuffingModePriority, dvbARExciterBInput1OKPriority, dvbARExciterBInput2OKPriority, dvbARExciterBLocalModePriority, 
				dvbARExciterBFaultPriority, dvbARExciterBWarningPriority, dvbARExciterBActiveInputPriority, dvbARExciterBSFNModePriority, dvbARExciterBMutePriority, 
				dvbARExciterBRefFaultPriority, dvbARExciterBFaultMIPPriority, dvbARExciterBStuffingModePriority }
			STATUS current
			DESCRIPTION 
				"Description. active reserve: object group"
			::= { groupsAR 1 }

		
		-- 1.3.6.1.4.1.19831.1.1.1.2.8.2
		eventGroupAR NOTIFICATION-GROUP
			NOTIFICATIONS { dvbARInputPreselectionEvent, dvbARInputAutomaticEvent, dvbARPreselectionExciterEvent, dvbARPreselectionAmplifierEvent, dvbARTransmitterOpModeEvent, 
				dvbARReserveControlEvent, dvbARActiveAmplifierEvent, dvbARActiveExciterEvent, dvbARLocalModeEvent, dvbARControlUnitFaultEvent, 
				dvbARExciterSwitchOverModeEvent, dvbARExciterSwitchOverReadyEvent, dvbARExciterSwitchOverExecutedEvent, dvbARExciterSwitchOverFaultEvent, dvbARAmplifierSwitchOverModeEvent, 
				dvbARAmplifierSwitchOverReadyEvent, dvbARAmplifierSwitchOverExecutedEvent, dvbARAmplifierSwitchOverFaultEvent, dvbARAmplifierARFPresentEvent, dvbARAmplifierAFaultEvent, 
				dvbARAmplifierAWarningEvent, dvbARAmplifierBRFPresentEvent, dvbARAmplifierBFaultEvent, dvbARAmplifierBWarningEvent, dvbARExciterAInput1OKEvent, 
				dvbARExciterAInput2OKEvent, dvbARExciterALocalModeEvent, dvbARExciterAFaultEvent, dvbARExciterAWarningEvent, dvbARExciterAActiveInputEvent, 
				dvbARExciterASFNModeEvent, dvbARExciterARefFaultEvent, dvbARExciterAMuteEvent, dvbARExciterAFaultMIPEvent, dvbARExciterAStuffingModeEvent, 
				dvbARExciterBInput1OKEvent, dvbARExciterBInput2OKEvent, dvbARExciterBLocalModeEvent, dvbARExciterBFaultEvent, dvbARExciterBWarningEvent, 
				dvbARExciterBActiveInputEvent, dvbARExciterBSFNModeEvent, dvbARExciterBRefFaultEvent, dvbARExciterBMuteEvent, dvbARExciterBFaultMIPEvent, 
				dvbARExciterBStuffingModeEvent }
			STATUS current
			DESCRIPTION 
				"Description. events"
			::= { groupsAR 2 }

		
		-- 1.3.6.1.4.1.19831.1.1.1.2.8.3
		objectGroupARobsolete OBJECT-GROUP
			OBJECTS { dvbARResetFault, dvbARResetFaultEnable, dvbARResetFaultPriority }
			STATUS obsolete
			DESCRIPTION 
				"Description. Inactive objects"
			::= { groupsAR 3 }

		
		-- 1.3.6.1.4.1.19831.1.1.1.2.8.4
		eventGroupARobsolete NOTIFICATION-GROUP
			NOTIFICATIONS { dvbARResetFaultEvent }
			STATUS obsolete
			DESCRIPTION 
				"Description. Inactive notifications"
			::= { groupsAR 4 }

		
		-- 1.3.6.1.4.1.19831.1.1.1.2.9
		complianceAR OBJECT IDENTIFIER ::= { dvbActiveReserve 9 }

		
		-- 1.3.6.1.4.1.19831.1.1.1.2.9.1
		dvbActiveReserveCompliance MODULE-COMPLIANCE
			STATUS current
			DESCRIPTION 
				"Compliance Statement"
			MODULE -- this module
				MANDATORY-GROUPS { objectGroupAR, eventGroupAR }
			::= { complianceAR 1 }

		
	
	END

--
-- IRT-DVBT-ACTIVERESERVE-MIB.my
--
