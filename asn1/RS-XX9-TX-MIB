--
-- RS-XX9-TX-MIB.mi2
-- MIB generated by MG-SOFT Visual MIB Builder 2010 Version 8.0  Build 403
-- Wednesday, May 04, 2016 at 14:21:13
--

-- *****************************************************************************
-- *****************************************************************************
-- **
-- **  COPYRIGHT      (c) 2011 Rohde & Schwarz GmbH & Co. KG
-- **                          Muehldorfstrasse 15
-- **    R & S                 D-81671 Muenchen
-- **
-- *****************************************************************************
-- **
-- **  MODULE         RS-XX9-TX-MIB
-- **  
-- *****************************************************************************
-- *****************************************************************************

    RS-XX9-TX-MIB DEFINITIONS ::= BEGIN
 
        IMPORTS
            InetAddressType, InetAddress            
                FROM INET-ADDRESS-MIB            
            commonNotificationAlarmClass            
                FROM RS-XX9-COMMON-MIB            
            rsXx9Tx, rsXx9MibModule            
                FROM RS-XX9-SMI-MIB            
            NotificationClass, IndexTransmitter, NotificationMask, NotificationPriority, NotificationState, 
            Trigger, SwitchOnOff, Xx9ModulationMode, IndexAB            
                FROM RS-XX9-TC-MIB            
            SnmpAdminString            
                FROM SNMP-FRAMEWORK-MIB            
            OBJECT-GROUP, MODULE-COMPLIANCE, NOTIFICATION-GROUP            
                FROM SNMPv2-CONF            
            Integer32, Unsigned32, Counter64, OBJECT-TYPE, MODULE-IDENTITY, 
            NOTIFICATION-TYPE            
                FROM SNMPv2-SMI            
            TruthValue, DateAndTime, TEXTUAL-CONVENTION            
                FROM SNMPv2-TC;
    
    
        rsXx9TxMibModule MODULE-IDENTITY 
            LAST-UPDATED "201605041500Z"		-- May 04, 2016 at 15:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines transmitter specific objects of
                XX9000 transmitting systems from Rohde & Schwarz
                that are independent of modulation mode.
                
                Use this MIB for things all transmitters support via SNMP.
                
                The following MIBs are related to this:
                - RS-COMMON-MIB         - mandatory for this MIB.
                - RS-XX9-SMI-MIB        - mandatory for this MIB.
                - RS-XX9-TC-MIB         - mandatory for this MIB.
                - RS-XX9-COMMON-MIB     - mandatory for this MIB."
            REVISION "201605041500Z"		-- May 04, 2016 at 15:00 GMT
            DESCRIPTION 
                "added txTransCmdWarnOnDohertyMismatch
                extended range for txPmxDohertyActive and txPhxDohertyActive
                added txRfLimitForwardAddUpperFail, txRfLimitForwardAddUpperWarn"
            REVISION "201604051500Z"		-- April 05, 2016 at 15:00 GMT
            DESCRIPTION 
                "added txPrecorrMerState notification
                added txPrecorrSigQualTable
                added txIpFeedLinkStatus
                "
            REVISION "201603080900Z"		-- March 08, 2016 at 09:00 GMT
            DESCRIPTION 
                "added txExcCmdOperationMode"
            REVISION "201601281100Z"		-- January 28, 2016 at 11:00 GMT
            DESCRIPTION 
                "txObjsPHx902 is also valid for PHU903"
            REVISION "201511300800Z"		-- November 30, 2015 at 08:00 GMT
            DESCRIPTION 
                "added edi options to txInpGsInputSource 
                "
            REVISION "201511261800Z"		-- November 26, 2015 at 18:00 GMT
            DESCRIPTION 
                "added txInpIfSatStreamTsIdMatch, txSatStreamCurrentTsId, txSatStreamExpectedTsId
                changed txSatLnbFreqLowBand, txSatLnbFreqHighBand, txSatLnbFreqCBand to read-only and add writable 32bit values instead"
            REVISION "201510191600Z"		-- October 19, 2015 at 16:00 GMT
            DESCRIPTION 
                "added txObjsPMU905 group
                obsoleted txPrecorrNonLinSetupSignalLimit 
                added more fine grained groups for linear precorrection, nonlinear precorrection and crest factor reduction
                added txExcCmdLoopControl
                extend txSatFeedServiceIdx to 0..32, extend txSatFeedDecryptionServiceIdx to 0..16, change access-level of txSatFeedInputServiceDecryption to read-write
                added more objects to txInputSatFeed subtree
                extended range of PrecorrectionState
                "
            REVISION "201507021200Z"		-- July 02, 2015 at 12:00 GMT
            DESCRIPTION 
                "increased range of txRfStReflectedVSWR with invalid value
                updated description texts
                move txSfnStateTimestampState into dvbt2-only group
                added Tlx Objects, including txAmplifierTlxTable
                make Objects in txObjsSFN1 group available for ATSC
                updated txInputSat description texts
                added statistical information to txInputIfFeedTable
                updated txSfnSetupSFN desciption text
                added txInpAutoFailDetection
                "
            REVISION "201412221600Z"		-- December 22, 2014 at 16:00 GMT
            DESCRIPTION 
                "added txRfIdentify, txRfCalibrate, txRfUncalibrate, txRfSensorCalibrated
                fixed value range of tfRfLimitReflectedVswrFail, txRfLimitReflectedVswrWarn
                changed ObjectGroup of txInpAutoDetectLostPackets to txObjsNonAnalog
                obsoleted txSatBtsRegionalization
                extended range of txAmpNotificationAmpIdx to 1..72 (for 6 racks)
                added txAmpBlocking, txTransCmdReflectionCheck, txTransCmdPrgOnAfterSumFault
                added ranges for txSatBtsPliTablePid, txSatBtsNullPacketLaPid, txSatBtsNullPacketLbPid, txSatBtsNullPacketLcPid
                updated description texts"
            REVISION "201410091400Z"		-- October 09, 2014 at 14:00 GMT
            DESCRIPTION 
                "added txInpAutoTransparentTs
                added txRfSensors subtree
                added txRfSensorLinkStatus
                fixed NotificationIdx ranges
                added txSfnStateTimestampState
                added txSatTunerIntermediateFreq, txSatTunerLinkMargin, txSatLnbBand, txSatLnbFreqCBand, txSatLnb22kHzSignal, txInpIfSatBtsStatus
                fixed txInpIfSat notification bindings
                added Description texts to txInputSat elements
                added txInputSatFeedDecryptionServiceTable, txInputSatFeedBtsTable
                change txSatCamBissInjectedId, txSatCamBissEncryptedSession, txSatCamBissClearSession: can not read encrypted content, write still possible
                added txFrqRegStateCurrentControllerMode
                re-enabled txInpAutoDelayInput1To2 (changed status from obsolete to current)
                change access of txSatFeedInputServiceDecryption to read-only
                reduce range of txSatFeedServiceIdx and txSatFeedDecryptionServiceIdx to 8 (was 16 before)
                obsoleted txSatFeedInputServiceDecryptedAt
                obsoleted txSatBtsDecompEnable"
            REVISION "201404301600Z"		-- April 30, 2014 at 16:00 GMT
            DESCRIPTION 
                "update txSummary value range: off not possible anymore
                added Preset
                txPmfFanFail now indicating FanFail with warning(4) instead of fault(3)
                added txInputSatFeedGeneralTable
                added MultiStandard nodes: txTransStPrimaryModMode, txTransStSecondaryModMode, txTransCmdChangeModulation
                added txTransStPaEfficiency
                changed access of txSatCamBissEncryptedSession to read-write
                added biss1 to txSatCamBissMode
                "
            REVISION "201402041700Z"		-- February 04, 2014 at 17:00 GMT
            DESCRIPTION 
                "obsoleted txInpAutoMaxDelayInput1To2 and txInpAutoDelayInput1To2
                added txInpIfLogDatarateBufferUnderrun and txInpIfLogDatarateBufferOverflow
                added ActiveReserve notifications, status and settings
                added txExciterAutomaticSummary notification
                added txInpAutoDetectLostPackets
                added sat1 and sat2 as options for txInpGsInputSource
                added sat receiver notifications, status and settings
                extended value range of txSfnStateSFN
                changes regarding txAmplifier section and txAmpXXX Notifications: 
                  - obsoleted txAmpDriverFail
                  - obsoleted txPmxAirFilterFail
                  - obsoleted txAmpStVReg
                  - obsoleted txPmxvRefPowerMax
                  - added txAmpOn notification
                  - fixes regarding validity of amplifier parameters for certain configurations
                  - updated description texts
                  - updated Unit scales in description texts
                  - added txPmxDohertyActive and txPhxDohertyActive
                "
            REVISION "201311181300Z"		-- November 18, 2013 at 13:00 GMT
            DESCRIPTION 
                "updated release with Switchless Combiner. 
                Switchless Combiner Tables are only filled, if a Switchless Combiner is configured. 
                updated FreqID for Pmx and Phx amplifiers: now using OCTET STRING syntax"
            REVISION "201303180800Z"		-- March 18, 2013 at 08:00 GMT
            DESCRIPTION 
                "Initial release."
            REVISION "201108190800Z"		-- August 19, 2011 at 08:00 GMT
            DESCRIPTION 
                "Preliminary release."
            ::= { rsXx9MibModule 3 }

        
    
--
-- Textual conventions
--
    
        PrecorrectionState ::= TEXTUAL-CONVENTION
            STATUS current
            DESCRIPTION 
                "idle(1)        - precorrector not active
                acquisition(2) - precorrector collects new measured values
                calculation(3) - precorrector calculates new curve
                checkResult(4) - precorrector checks result for plausibility
                
                "
            SYNTAX INTEGER
                {
                idle(1),
                acquisition(2),
                calculation(3),
                checkResult(4)
                }

        PrecorrectionSignalLevel ::= TEXTUAL-CONVENTION
            STATUS current
            DESCRIPTION 
                "State of RF input level:
                ok(2)      - level is within operation area
                tooLow(3)  - level is too low
                tooHigh(4) - level is too high
                noInput(5) - no input for run mode"
            SYNTAX INTEGER
                {
                undefined(1),
                ok(2),
                tooLow(3),
                tooHigh(4),
                noInput(5)
                }

        PrecorrectionOperationMode ::= TEXTUAL-CONVENTION
            STATUS current
            DESCRIPTION 
                "bypass(1) - precorrector is deactivated,
                            input signal is not modified
                stop(2)   - automatic precorrection is deactivated,
                            input signal is modified from a constant curve
                run(4)    - automatic precorrection is active"
            SYNTAX INTEGER
                {
                bypass(1),
                stop(2),
                run(4)
                }

        AutomaticMode ::= TEXTUAL-CONVENTION
            STATUS current
            DESCRIPTION 
                "Determines behaviour after successful switching:
                severalTimes(1) - automatic switches back autonomously to the
                                  preselected exciter if the reserve exciter is faulty
                                  and the preselected exciter is ready
                singleShot(2)   - "
            SYNTAX INTEGER
                {
                severalTimes(1),
                singleShot(2)
                }

        SatSignalType ::= TEXTUAL-CONVENTION
            STATUS current
            DESCRIPTION 
                "Description."
            SYNTAX INTEGER
                {
                undefinedType(1),
                dvbs(2),
                dvbs2(3),
                dss(4),
                auto(5)
                }

        ControllerMode ::= TEXTUAL-CONVENTION
            STATUS current
            DESCRIPTION 
                "Description."
            SYNTAX INTEGER
                {
                standard(1),
                jitter(2)
                }

        DohertyActive ::= TEXTUAL-CONVENTION
            STATUS current
            DESCRIPTION 
                "Description."
            SYNTAX INTEGER
                {
                true(1),
                false(2),
                warning(4)
                }

    
--
-- Node definitions
--
    
        rsXx9TxNotifications OBJECT IDENTIFIER ::= { rsXx9Tx 0 }

        
        txSummary NOTIFICATION-TYPE
            OBJECTS { commonNotificationAlarmClass, txTransmitterNotificationPriority, txTransmitterNotificationState }
            STATUS current
            DESCRIPTION 
                "Transmitter summary state.
                
                Possible values:
                fault(3)
                warning(4)
                ok(5)
                
                Notification class: fault"
            ::= { rsXx9TxNotifications 1 }

        
        txRF NOTIFICATION-TYPE
            OBJECTS { commonNotificationAlarmClass, txTransmitterNotificationPriority, txTransmitterNotificationState }
            STATUS current
            DESCRIPTION 
                "indicates a warning/fault if RF power falls below the adjusted warning/fault limit. 
                
                Possible values:
                off(2)
                fault(3)
                warning(4)
                ok(5)
                
                Notification class: fault"
            ::= { rsXx9TxNotifications 2 }

        
        txReflection NOTIFICATION-TYPE
            OBJECTS { commonNotificationAlarmClass, txTransmitterNotificationPriority, txTransmitterNotificationState }
            STATUS current
            DESCRIPTION 
                "The reflected RF is above warning or fault limit. 
                
                Possible values:
                off(2)
                fault(3)
                warning(4)
                ok(5)
                
                Notification class: fault"
            ::= { rsXx9TxNotifications 3 }

        
        txRfSensorSummary NOTIFICATION-TYPE
            OBJECTS { commonNotificationAlarmClass, txTransmitterNotificationPriority, txTransmitterNotificationState }
            STATUS current
            DESCRIPTION 
                "RF sensor summary state.
                
                Possible values:
                off(2)
                fault(3)
                warning(4)
                ok(5)
                
                Notification class: fault"
            ::= { rsXx9TxNotifications 4 }

        
        txLocal NOTIFICATION-TYPE
            OBJECTS { commonNotificationAlarmClass, txTransmitterNotificationPriority, txTransmitterNotificationState }
            STATUS current
            DESCRIPTION 
                "local/remote state of transmitter.
                
                Possible values:
                off(2)   - remote
                ok(5)    - local
                
                Notification class: info"
            ::= { rsXx9TxNotifications 5 }

        
        txExciterAutomaticOn NOTIFICATION-TYPE
            OBJECTS { commonNotificationAlarmClass, txTransmitterNotificationPriority, txTransmitterNotificationState }
            STATUS current
            DESCRIPTION 
                "Shows whether the exciter automatic is activated.
                
                Possible values:
                off(2) - not activated
                ok(5)  - activated
                
                Notification class: info"
            ::= { rsXx9TxNotifications 6 }

        
        txExciterAutomaticReady NOTIFICATION-TYPE
            OBJECTS { commonNotificationAlarmClass, txTransmitterNotificationPriority, txTransmitterNotificationState }
            STATUS current
            DESCRIPTION 
                "Indicates whether the automatic exciter switchover function is 
                ready. 
                
                off(2) - not ready: The standby exciter is not operational, the 
                transmitter is switched off, the automatic switchover function 
                already switched over or there is a defect in the exciter switch.
                ok(5)  - ready: The automatic switchover function is operational. 
                
                Notification class: info
                "
            ::= { rsXx9TxNotifications 7 }

        
        txExciterAutomaticSwitchedOver NOTIFICATION-TYPE
            OBJECTS { commonNotificationAlarmClass, txTransmitterNotificationPriority, txTransmitterNotificationState }
            STATUS current
            DESCRIPTION 
                "Indicates whether the exciter automatic switched
                to a reserve exciter.
                
                Possible values:
                off(2)     - not switched
                warning(4) - switched
                
                Notification class: warning"
            ::= { rsXx9TxNotifications 8 }

        
        txExciterAutomaticRfSwitchSummary NOTIFICATION-TYPE
            OBJECTS { commonNotificationAlarmClass, txTransmitterNotificationPriority, txTransmitterNotificationState }
            STATUS current
            DESCRIPTION 
                "RF switch summary state.
                Indicates that the exciter switch does not work properly. 
                Check the two CAN-bus cables between exciter switch 
                and TCE900-Exciter A and B. Whether the cabling is ok 
                the exciter switch has to be replaced.
                
                Possible values:
                ok(5)
                "
            ::= { rsXx9TxNotifications 9 }

        
        txExciterAutomaticSummary NOTIFICATION-TYPE
            STATUS current
            DESCRIPTION 
                "the sum state of the exciter automatic
                
                Possible values:
                off(2) - automatic off
                fault(3) - automatic fail or RfSwitch not connected
                warning(4) - switchover occurred
                ok(5) - ready
                
                Notification class: warning"
            ::= { rsXx9TxNotifications 10 }

        
        txActiveReserveExcAutoOn NOTIFICATION-TYPE
            STATUS current
            DESCRIPTION 
                "Description."
            ::= { rsXx9TxNotifications 1000 }

        
        txActiveReserveExcAutoReady NOTIFICATION-TYPE
            OBJECTS { commonNotificationAlarmClass, txTransmitterNotificationPriority, txTransmitterNotificationState }
            STATUS current
            DESCRIPTION 
                "Indicates whether the automatic exciter switchover function is 
                ready. 
                
                ok(5) - Ready: The automatic switchover function is operational. 
                off(2) - Not Ready: The standby exciter is not operational, the 
                transmitter is switched off, the automatic switchover function 
                already switched over or there is a defect in the exciter switch.
                "
            ::= { rsXx9TxNotifications 1001 }

        
        txActiveReserveExcAutoSwitchedOver NOTIFICATION-TYPE
            OBJECTS { commonNotificationAlarmClass, txTransmitterNotificationPriority, txTransmitterNotificationState }
            STATUS current
            DESCRIPTION 
                "Description."
            ::= { rsXx9TxNotifications 1002 }

        
        txActiveReserveExcAutoRfSwitchSummary NOTIFICATION-TYPE
            OBJECTS { commonNotificationAlarmClass, txTransmitterNotificationPriority, txTransmitterNotificationState }
            STATUS current
            DESCRIPTION 
                "Indicates whether the exciter switch is working. If a switchover to 
                the standby exciter fails, an error is displayed.
                "
            ::= { rsXx9TxNotifications 1003 }

        
        txActiveReserveExcAutoSummary NOTIFICATION-TYPE
            OBJECTS { commonNotificationAlarmClass, txTransmitterNotificationPriority, txTransmitterNotificationState }
            STATUS current
            DESCRIPTION 
                "Description."
            ::= { rsXx9TxNotifications 1004 }

        
        txActiveReserveOstAutoOn NOTIFICATION-TYPE
            STATUS current
            DESCRIPTION 
                "Description."
            ::= { rsXx9TxNotifications 1500 }

        
        txActiveReserveOstAutoReady NOTIFICATION-TYPE
            OBJECTS { commonNotificationAlarmClass, txTransmitterNotificationPriority, txTransmitterNotificationState }
            STATUS current
            DESCRIPTION 
                "Description."
            ::= { rsXx9TxNotifications 1501 }

        
        txActiveReserveOstAutoSwitchedOver NOTIFICATION-TYPE
            OBJECTS { commonNotificationAlarmClass, txTransmitterNotificationPriority, txTransmitterNotificationState }
            STATUS current
            DESCRIPTION 
                "Description."
            ::= { rsXx9TxNotifications 1502 }

        
        txActiveReserveOstAutoRfSwitchSummary NOTIFICATION-TYPE
            OBJECTS { commonNotificationAlarmClass, txTransmitterNotificationPriority, txTransmitterNotificationState }
            STATUS current
            DESCRIPTION 
                "Description."
            ::= { rsXx9TxNotifications 1503 }

        
        txActiveReserveOstAutoSummary NOTIFICATION-TYPE
            OBJECTS { commonNotificationAlarmClass, txTransmitterNotificationPriority, txTransmitterNotificationState }
            STATUS current
            DESCRIPTION 
                "Description."
            ::= { rsXx9TxNotifications 1504 }

        
        txExciterSummary NOTIFICATION-TYPE
            OBJECTS { commonNotificationAlarmClass, txExciterNotificationPriority, txExciterNotificationState }
            STATUS current
            DESCRIPTION 
                "Exciter summary state.
                
                Possible values:
                off(2)
                fault(3)
                warning(4)
                ok(5)
                
                Notification class: fault"
            ::= { rsXx9TxNotifications 2000 }

        
        txExciterLoop NOTIFICATION-TYPE
            OBJECTS { commonNotificationAlarmClass, txExciterNotificationPriority, txExciterNotificationState }
            STATUS current
            DESCRIPTION 
                "Indicates whether the protection loop is open.
                
                Possible values:
                warning(4) - loop is open
                ok(5)      - loop is closed
                
                Notification class: warning"
            ::= { rsXx9TxNotifications 2001 }

        
        txExciterMute NOTIFICATION-TYPE
            OBJECTS { commonNotificationAlarmClass, txExciterNotificationPriority, txExciterNotificationState }
            STATUS current
            DESCRIPTION 
                "Indicates whether the RF output of the exciter is muted.
                
                Possible values:
                warning(4) - mute
                ok(5)      - no mute
                
                Notification class: warning"
            ::= { rsXx9TxNotifications 2002 }

        
        txExciterOutputConnect NOTIFICATION-TYPE
            OBJECTS { commonNotificationAlarmClass, txExciterNotificationPriority, txExciterNotificationState }
            STATUS current
            DESCRIPTION 
                "Indicates whether a RF connection between
                exciter output and amplifier input exists.
                
                Possible values:
                fault(3) - no connection
                ok(5)
                
                Notification class: fault"
            ::= { rsXx9TxNotifications 2003 }

        
        txExciterRfState NOTIFICATION-TYPE
            OBJECTS { commonNotificationAlarmClass, txExciterNotificationPriority, txExciterNotificationState }
            STATUS current
            DESCRIPTION 
                "Indicates whether a RF signal with sufficient
                level is output.
                
                Possible values:
                off(2)     - no signal
                fault(3)   - signal level lower fault limit
                warning(4) - signal level lower warning limit
                ok(5)      - signal level ok
                
                Notification class: fault"
            ::= { rsXx9TxNotifications 2004 }

        
        txInpIfLogState NOTIFICATION-TYPE
            OBJECTS { commonNotificationAlarmClass, txInpIfNotificationPriority, txInpIfNotificationState }
            STATUS current
            DESCRIPTION 
                "State of logical input.
                Indicates whether a valid serial data stream is being fed to the transmitter.
                
                Possible values:
                off(2)     - no signal
                fault(3)
                warning(4)
                ok(5)
                
                Notification class: fault"
            ::= { rsXx9TxNotifications 3000 }

        
        txInpIfLogInfoPacket NOTIFICATION-TYPE
            OBJECTS { commonNotificationAlarmClass, txInpIfNotificationPriority, txInpIfNotificationState }
            STATUS current
            DESCRIPTION 
                "state of the information packet 
                (MIP, IIP or TCP: depends on transmitting standard).
                
                Possible values:
                off(2)     - 
                fault(3)
                warning(4)
                ok(5)
                
                Notification class: fault"
            ::= { rsXx9TxNotifications 3001 }

        
        txInpIfLogPacketLength NOTIFICATION-TYPE
            OBJECTS { commonNotificationAlarmClass, txInpIfNotificationPriority, txInpIfNotificationState }
            STATUS current
            DESCRIPTION 
                "Indicates whether the detected packet length can be used.
                
                Possible values:
                off(2)
                warning(4)
                ok(5)
                
                Notification class: warning"
            ::= { rsXx9TxNotifications 3002 }

        
        txInpIfIpState NOTIFICATION-TYPE
            OBJECTS { commonNotificationAlarmClass, txInpIfNotificationPriority, txInpIfNotificationState }
            STATUS current
            DESCRIPTION 
                "Indicates whether a valid data stream is fed
                to the transmitter via the IP feed.
                If an error is indicated, check the settings of the IP stream and the Ethernet interface.
                
                Possible values:
                off(2)     - no stream
                fault(3)
                warning(4)
                ok(5)
                
                Notification class: warning"
            ::= { rsXx9TxNotifications 3003 }

        
        txInpIfIpInfoPacket NOTIFICATION-TYPE
            OBJECTS { commonNotificationAlarmClass, txInpIfNotificationPriority, txInpIfNotificationState }
            STATUS current
            DESCRIPTION 
                "Indicates the state of the information packet.
                
                Possible values:
                off(2)     - 
                fault(3)
                warning(4)
                ok(5)
                
                Notification class: warning"
            ::= { rsXx9TxNotifications 3004 }

        
        txInpIfIpPacketLength NOTIFICATION-TYPE
            OBJECTS { commonNotificationAlarmClass, txInpIfNotificationPriority, txInpIfNotificationState }
            STATUS current
            DESCRIPTION 
                "Indicates whether the detected packet length can be used.
                
                Possible values:
                warning(4)
                ok(5)
                
                Notification class: warning"
            ::= { rsXx9TxNotifications 3005 }

        
        txInpIfTsState NOTIFICATION-TYPE
            OBJECTS { commonNotificationAlarmClass, txInpIfNotificationPriority, txInpIfNotificationState }
            STATUS current
            DESCRIPTION 
                "Indicates whether a valid serial data stream is fed
                to the transmitter via TS1/2 IN (X20/X21).
                If an error is displayed here, first check the setting of the TS type (ASI/SMPTE).
                
                Possible values:
                off(2)     - no stream
                fault(3)
                warning(4)
                ok(5)
                
                Notification class: warning"
            ::= { rsXx9TxNotifications 3006 }

        
        txInpIfTsInfoPacket NOTIFICATION-TYPE
            OBJECTS { commonNotificationAlarmClass, txInpIfNotificationPriority, txInpIfNotificationState }
            STATUS current
            DESCRIPTION 
                "Indicates whether the control information required for SFN mode is 
                contained in the data stream. The displayed name depends on the 
                modulation standard. An error can also be displayed in MFN mode 
                if the coder settings are to be controlled automatically via the 
                transport stream.
                
                Possible values:
                off(2)     - not required
                fault(3)
                warning(4)
                ok(5)
                
                Notification class: warning"
            ::= { rsXx9TxNotifications 3007 }

        
        txInpIfTsPacketLength NOTIFICATION-TYPE
            OBJECTS { commonNotificationAlarmClass, txInpIfNotificationPriority, txInpIfNotificationState }
            STATUS current
            DESCRIPTION 
                "Indicates whether the detected packet length cannot be used.
                
                Possible values:
                warning(4)
                ok(5)
                
                Notification class: warning"
            ::= { rsXx9TxNotifications 3008 }

        
        txInpIfLogDatarateBufferUnderrun NOTIFICATION-TYPE
            OBJECTS { commonNotificationAlarmClass, txInpIfNotificationPriority, txInpIfNotificationState }
            STATUS current
            DESCRIPTION 
                "Indicates a too low datarate at this Input. In 
                SFNs the datarate is defined by the coder 
                settings. In MFNs the Input datarate might 
                be lower, but must not exceed the minimum 
                defined datarate by coder settings over a 
                longer period.
                
                Possible values:
                off(2)
                warning(4)
                ok(5)
                
                Notification class: warning"
            ::= { rsXx9TxNotifications 3009 }

        
        txInpIfLogDatarateBufferOverflow NOTIFICATION-TYPE
            OBJECTS { commonNotificationAlarmClass, txInpIfNotificationPriority, txInpIfNotificationState }
            STATUS current
            DESCRIPTION 
                "Indicates a too high datarate at this Input. In 
                SFNs the datarate is defined by the coder 
                settings. In MFNs the Input datarate must 
                not exceed the maximum defined datarate 
                by coder settings over a longer period.
                
                Possible values:
                off(2)
                warning(4)
                ok(5)
                
                Notification class: warning"
            ::= { rsXx9TxNotifications 3010 }

        
        txInpIfSatInputState NOTIFICATION-TYPE
            OBJECTS { commonNotificationAlarmClass, txInpIfNotificationPriority, txInpIfNotificationState }
            STATUS current
            DESCRIPTION 
                "Indicates whether a valid data stream is fed to the transmitter via the SAT feed. 
                
                Possible values:
                off(2) - no stream
                fault(3)
                warning(4)
                ok(5)"
            ::= { rsXx9TxNotifications 3011 }

        
        txInpIfSatInfoPacket NOTIFICATION-TYPE
            OBJECTS { commonNotificationAlarmClass, txInpIfNotificationPriority, txInpIfNotificationState }
            STATUS current
            DESCRIPTION 
                "Indicates the state of the information packet.
                
                Possible values:
                off(2) - not required
                fault(3)
                warning(4)
                ok(5)"
            ::= { rsXx9TxNotifications 3012 }

        
        txInpIfSatPacketLength NOTIFICATION-TYPE
            OBJECTS { commonNotificationAlarmClass, txInpIfNotificationPriority, txInpIfNotificationState }
            STATUS current
            DESCRIPTION 
                "Indicates whether the detected packet length cannot be used.
                
                Possible values:
                warning(4)
                ok(5)"
            ::= { rsXx9TxNotifications 3013 }

        
        txInpIfSatTransponderLocked NOTIFICATION-TYPE
            OBJECTS { commonNotificationAlarmClass, txInpIfNotificationPriority, txInpIfNotificationState }
            STATUS current
            DESCRIPTION 
                "Indicates if the DVB-S/S2 Receiver has locked to a signal.
                
                Possible values:
                warning(4)
                ok(5)"
            ::= { rsXx9TxNotifications 3014 }

        
        txInpIfSatIpOutput NOTIFICATION-TYPE
            OBJECTS { commonNotificationAlarmClass, txInpIfNotificationPriority, txInpIfNotificationState }
            STATUS current
            DESCRIPTION 
                "Description."
            ::= { rsXx9TxNotifications 3015 }

        
        txInpIfSatReceiverState NOTIFICATION-TYPE
            OBJECTS { commonNotificationAlarmClass, txInpIfNotificationPriority, txInpIfNotificationState }
            STATUS current
            DESCRIPTION 
                "Description.
                
                Possible values:
                off(2)
                fault(3)
                warning(4)
                ok(5)"
            ::= { rsXx9TxNotifications 3016 }

        
        txInpIfSatBtsStatus NOTIFICATION-TYPE
            OBJECTS { commonNotificationAlarmClass, txInpIfNotificationPriority, txInpIfNotificationState }
            STATUS current
            DESCRIPTION 
                "Description.
                
                Possible values:
                off(2)
                fault(3)
                option not installed(4)
                ok(5)
                
                Notification class: info"
            ::= { rsXx9TxNotifications 3017 }

        
        txInpIfSatDriftStatus NOTIFICATION-TYPE
            OBJECTS { commonNotificationAlarmClass, txInpIfNotificationPriority, txInpIfNotificationState }
            STATUS current
            DESCRIPTION 
                "Indicates a warning when the difference between transponder frequency 
                and receive frequency (tuner frequency) is too high.
                
                Possible values:
                off(2)
                warning(4)
                ok(5)
                "
            ::= { rsXx9TxNotifications 3018 }

        
        txInpIfSatLinkMarginStatus NOTIFICATION-TYPE
            OBJECTS { commonNotificationAlarmClass, txInpIfNotificationPriority, txInpIfNotificationState }
            STATUS current
            DESCRIPTION 
                "Indicates whether the attenuation is low enough for failure-free operation. 
                The thresholds for generating a warning or a fault can be adjusted.
                
                Possible values:
                off(2)
                fault(3)
                warning(4)
                ok(5)
                "
            ::= { rsXx9TxNotifications 3019 }

        
        txInpIfSatCarrierNoiseStatus NOTIFICATION-TYPE
            OBJECTS { commonNotificationAlarmClass, txInpIfNotificationPriority, txInpIfNotificationState }
            STATUS current
            DESCRIPTION 
                "Indicates whether the current carrier to noise ratio is below the warning limit. 
                
                Possible values:
                off(2)
                fault(3)
                warning(4)
                ok(5)
                "
            ::= { rsXx9TxNotifications 3020 }

        
        txInpIfSatStreamTsIdMatch NOTIFICATION-TYPE
            OBJECTS { commonNotificationAlarmClass, txTransmitterNotificationPriority, txTransmitterNotificationState }
            STATUS current
            DESCRIPTION 
                "Indicates whether the current TS ID is equal to the expected TS ID.
                Changing the ID in transport stream leads to a warning. 
                Setting the expected TS ID to zero suppresses a warning.  
                
                "
            ::= { rsXx9TxNotifications 3021 }

        
        txInpAuto1Active NOTIFICATION-TYPE
            OBJECTS { commonNotificationAlarmClass, txInpAutoNotificationPriority, txInpAutoNotificationState }
            STATUS current
            DESCRIPTION 
                "Shows whether input1 or input2 is used for RF modulation.
                
                Possible values:
                off(2) - input2 is active
                ok(5)  - input1 is active
                
                Notification class: info"
            ::= { rsXx9TxNotifications 4000 }

        
        txInpAutoState NOTIFICATION-TYPE
            OBJECTS { commonNotificationAlarmClass, txInpAutoNotificationPriority, txInpAutoNotificationState }
            STATUS current
            DESCRIPTION 
                "Indicates the state of the automatic input signal
                switchover function.
                
                Possible values:
                off(2)       - The automatic switchover function is not enabled.
                warning(4)   - The automatic switchover function has switched over
                               from the preferred input to the standby input.
                ok(5)        - The automatic switchover function is ready to switch
                               the current input over to the input currently not in
                               use as soon as the input signal of the current input fails. 
                
                Notification class: warning"
            ::= { rsXx9TxNotifications 4001 }

        
        txFrqRegSummary NOTIFICATION-TYPE
            OBJECTS { commonNotificationAlarmClass, txFrqRegNotificationPriority, txFrqRegNotificationState }
            STATUS current
            DESCRIPTION 
                "Indicates the state of the reference used.
                In single-frequency networks, a failure of the reference
                can cause a malfunction and thus replacement of the exciter.
                
                Possible values:
                off(2)     - txFrqRegSetupSource is manual(1)
                fault(3)
                warning(4)
                ok(5)
                
                Notification class: warning"
            ::= { rsXx9TxNotifications 5000 }

        
        txFrqRegCurrentSource NOTIFICATION-TYPE
            OBJECTS { commonNotificationAlarmClass, txFrqRegNotificationPriority, txFrqRegNotificationState }
            STATUS current
            DESCRIPTION 
                "Quality of current reference source.
                
                Possible values:
                off(2)     - no signal
                fault(3)  - missing
                warning(4) - inaccurate
                ok(5)      - good
                
                Notification class: warning"
            ::= { rsXx9TxNotifications 5001 }

        
        txFrqRegSourceExtRef NOTIFICATION-TYPE
            OBJECTS { commonNotificationAlarmClass, txFrqRegNotificationPriority, txFrqRegNotificationState }
            STATUS current
            DESCRIPTION 
                "Indicates whether a reference signal is present
                at the REF_IN (X64) jack at the TCE.
                
                Possible values:
                off(2)     - no signal
                fault(3)  - missing
                warning(4) - inaccurate
                ok(5)      - good
                
                Notification class: warning"
            ::= { rsXx9TxNotifications 5002 }

        
        txFrqRegSourceExtPPS NOTIFICATION-TYPE
            OBJECTS { commonNotificationAlarmClass, txFrqRegNotificationPriority, txFrqRegNotificationState }
            STATUS current
            DESCRIPTION 
                "Indicates whether a seconds pulse is present
                at the 1PPS_IN (X23) jack at the TCE.
                
                Possible values:
                off(2)     - no signal
                fault(3)  - missing
                warning(4) - inaccurate
                ok(5)      - good
                
                Notification class: warning"
            ::= { rsXx9TxNotifications 5003 }

        
        txFrqRegSourceIntGPS NOTIFICATION-TYPE
            OBJECTS { commonNotificationAlarmClass, txFrqRegNotificationPriority, txFrqRegNotificationState }
            STATUS current
            DESCRIPTION 
                "Quality of the internal GPS reference source.
                
                Possible values:
                off(2)     - no signal
                fault(3)  - missing
                warning(4) - inaccurate
                ok(5)      - good
                
                Notification class: warning"
            ::= { rsXx9TxNotifications 5004 }

        
        txSfnSummary NOTIFICATION-TYPE
            OBJECTS { commonNotificationAlarmClass, txSfnNotificationPriority, txSfnNotificationState }
            STATUS current
            DESCRIPTION 
                "Time synchronization summary.
                Contains: time reference, time information, mode state
                
                Possible values:
                off(2)
                warning(4)
                ok(5)      - on
                
                Notification class: warning"
            ::= { rsXx9TxNotifications 6000 }

        
        txPrecorrLinSummary NOTIFICATION-TYPE
            OBJECTS { commonNotificationAlarmClass, txPrecorrNotificationPriority, txPrecorrNotificationState }
            STATUS current
            DESCRIPTION 
                "Linear precorrection summary state.
                
                Possible values:
                off(2)
                warning(4)
                ok(5)
                
                Notification class: warning"
            ::= { rsXx9TxNotifications 8000 }

        
        txPrecorrNonLinSummary NOTIFICATION-TYPE
            OBJECTS { commonNotificationAlarmClass, txPrecorrNotificationPriority, txPrecorrNotificationState }
            STATUS current
            DESCRIPTION 
                "Non linear precorrection summary state.
                
                Possible values:
                off(2)
                warning(4)
                ok(5)
                
                Notification class: warning"
            ::= { rsXx9TxNotifications 8001 }

        
        txPrecorrMerState NOTIFICATION-TYPE
            OBJECTS { commonNotificationAlarmClass, txPrecorrNotificationPriority, txPrecorrNotificationState }
            STATUS current
            DESCRIPTION 
                "Description."
            ::= { rsXx9TxNotifications 8002 }

        
        txOstSummary NOTIFICATION-TYPE
            OBJECTS { commonNotificationAlarmClass, txOstNotificationPriority, txOstNotificationState }
            STATUS current
            DESCRIPTION 
                "Output stage summary state.
                
                Possible values:
                off(2)
                fault(3)
                warning(4)
                ok(5)
                
                Notification class: fault"
            ::= { rsXx9TxNotifications 9000 }

        
        txAmpSummary NOTIFICATION-TYPE
            OBJECTS { commonNotificationAlarmClass, txAmpNotificationPriority, txAmpNotificationState }
            STATUS current
            DESCRIPTION 
                "Amplifier summary state.
                
                Possible values:
                off(2)
                fault(3)
                warning(4)
                ok(5)
                
                Notification class: fault"
            ::= { rsXx9TxNotifications 10000 }

        
        txAmpRfPowerFail NOTIFICATION-TYPE
            OBJECTS { commonNotificationAlarmClass, txAmpNotificationPriority, txAmpNotificationState }
            STATUS current
            DESCRIPTION 
                " Indicates that the output power of the amplifier is more than 
                3 dB below the reference value.
                
                Possible values:
                off(2)   - RF power ok
                fault(3) - the output power of the amplifier is more than
                           3 dB below the reference value.
                
                Notification class: fault"
            ::= { rsXx9TxNotifications 10001 }

        
        txAmpReflection NOTIFICATION-TYPE
            OBJECTS { commonNotificationAlarmClass, txAmpNotificationPriority, txAmpNotificationState }
            STATUS current
            DESCRIPTION 
                "Indicates whether reflection at the RF output is becoming too great. 
                In this case, the antenna as well as the link between the amplifiers 
                and the antenna via the combiners and output-stage switches 
                (if present) must be checked.
                
                Possible values:
                off(2)
                warning(4) - reflection at the RF output is too great
                
                Notification class: warning"
            ::= { rsXx9TxNotifications 10002 }

        
        txAmpSupplyFail NOTIFICATION-TYPE
            OBJECTS { commonNotificationAlarmClass, txAmpNotificationPriority, txAmpNotificationState }
            STATUS current
            DESCRIPTION 
                "Indicates whether the internal power supply units are functioning correctly. 
                
                Possible values:
                off(2)   - internal power supply units are functioning correctly
                fault(3)
                
                Notification class: fault"
            ::= { rsXx9TxNotifications 10003 }

        
        txAmpRfInFail NOTIFICATION-TYPE
            OBJECTS { commonNotificationAlarmClass, txAmpNotificationPriority, txAmpNotificationState }
            STATUS current
            DESCRIPTION 
                "Indicates that the amplifier is receiving an input signal, 
                the level of which is too low. 
                
                - If this message occurs at all amplifiers at the same time, 
                  the fault is located at the exciter switch, splitter or exciter. 
                - If this fault occurs at only some of the amplifiers, the 
                  output level of the exciters and splitter must be checked. 
                - If the fault occurs at only one amplifier, the self-engaging 
                  connector of the RF signal on the rear panel of the amplifier 
                  must be checked for mechanical damage.
                
                Possible values:
                off(2)
                warning(4) - the amplifier is receiving an input signal,
                             the level of which is too low
                
                Notification class: warning"
            ::= { rsXx9TxNotifications 10004 }

        
        txAmpMute NOTIFICATION-TYPE
            OBJECTS { commonNotificationAlarmClass, txAmpNotificationPriority, txAmpNotificationState }
            STATUS current
            DESCRIPTION 
                "Indicates that the amplifier is suppressing its output signal. 
                This indicator appears in the following cases: 
                - No input signal 
                - During bias adjustment 
                - An external absorber signals that it is overheating.
                
                Possible values:
                off(2)
                warning(4) - the amplifier is suppressing its output signal
                
                Notification class: warning"
            ::= { rsXx9TxNotifications 10005 }

        
        txAmpTemperatureFail NOTIFICATION-TYPE
            OBJECTS { commonNotificationAlarmClass, txAmpNotificationPriority, txAmpNotificationState }
            STATUS current
            DESCRIPTION 
                "Indicates that the amplifier is overheating internally. 
                - With liquid-cooled amplifiers, this fault can occur if 
                  the stop valves have been closed inadvertently. 
                - With air-cooled amplifiers, it must be checked whether 
                  the air inflow or outflow is obstructed or the inflow air 
                  temperature is too high.
                
                Possible values:
                off(2)
                fault(3) - the amplifier is overheating internally
                
                Notification class: fault"
            ::= { rsXx9TxNotifications 10006 }

        
        txAmpTransistorFail NOTIFICATION-TYPE
            OBJECTS { commonNotificationAlarmClass, txAmpNotificationPriority, txAmpNotificationState }
            STATUS current
            DESCRIPTION 
                "Indicates that one or more driver or power transistors are defective. 
                Only personnel with the relevant special service training are 
                permitted to change the transistors.
                
                Possible values:
                off(2)
                fault(3) - one or more driver or power transistors are defective
                
                Notification class: fault"
            ::= { rsXx9TxNotifications 10007 }

        
        txAmpRegulationFail NOTIFICATION-TYPE
            OBJECTS { commonNotificationAlarmClass, txAmpNotificationPriority, txAmpNotificationState }
            STATUS current
            DESCRIPTION 
                "This error occurs if the internal power regulation of the amplifier 
                reaches the limit of its control range. This indicates one or more 
                defective power transistors.
                
                Possible values:
                off(2)
                fault(3) - the internal power regulation of the amplifier
                           reaches the limit of its control range
                
                Notification class: fault"
            ::= { rsXx9TxNotifications 10008 }

        
        txAmpAcFail NOTIFICATION-TYPE
            OBJECTS { commonNotificationAlarmClass, txAmpNotificationPriority, txAmpNotificationState }
            STATUS current
            DESCRIPTION 
                "indicates if one of the power supplies are faulty. 
                A fault can only be indicated if the RF of transmitter 
                is switched on (Program=On).
                
                Possible values:
                off(2)
                warning(4) - one of the power supplies is faulty
                
                Notification class: warning"
            ::= { rsXx9TxNotifications 10009 }

        
        txAmpDcFail NOTIFICATION-TYPE
            OBJECTS { commonNotificationAlarmClass, txAmpNotificationPriority, txAmpNotificationState }
            STATUS current
            DESCRIPTION 
                "Indicates whether one of the internal power supply units of the amplifier 
                is faulty (e.g. no DC voltage is being delivered). Detection of a fault is 
                only possible if the RF of the transmitter has been switched on (Program=On).
                
                Possible values:
                off(2)
                fault(3) - one of the internal power supply units of the amplifier is faulty
                
                Notification class: fault"
            ::= { rsXx9TxNotifications 10010 }

        
        txAmpDriverFail NOTIFICATION-TYPE
            OBJECTS { commonNotificationAlarmClass, txAmpNotificationPriority, txAmpNotificationState }
            STATUS obsolete
            DESCRIPTION 
                "indicates that the driver transistors are damaged. 
                If this error occurs the amplifier has to be repaired 
                by trained service personnel
                
                Possible values:
                off(2)
                fault(3) - the driver transistors are damaged
                
                Notification class: fault"
            ::= { rsXx9TxNotifications 10011 }

        
        txAmpLink NOTIFICATION-TYPE
            OBJECTS { commonNotificationAlarmClass, txAmpNotificationPriority, txAmpNotificationState }
            STATUS current
            DESCRIPTION 
                "status of the communication link to the TCE900. 
                
                Possible values:
                warning(4) - communication link is not ok 
                ok(5)      - communication link is ok
                
                Notification class: warning"
            ::= { rsXx9TxNotifications 10012 }

        
        txAmpBiasFail NOTIFICATION-TYPE
            OBJECTS { commonNotificationAlarmClass, txAmpNotificationPriority, txAmpNotificationState }
            STATUS current
            DESCRIPTION 
                "Indicates a fault if the quiescent current of one or more transistors
                cannot be adjusted.
                
                Possible values:
                off(2)     - Amplifier error: There is a technical fault in the amplifier;
                             the amplifier should be replaced.
                fault(3)   - Adjustment has been aborted because a constant temperature has not
                             settled in the amplifier. In this case, adjustment should be started
                             again immediately after the fault has occurred.
                warning(4) - Adjust error: There is a technical fault in the amplifier;
                             the amplifier should be replaced.
                ok(5)      - Automatic quiescent current adjustment has been performed properly.
                
                Notification class: warning"
            ::= { rsXx9TxNotifications 10013 }

        
        txAmpInitFail NOTIFICATION-TYPE
            OBJECTS { commonNotificationAlarmClass, txAmpNotificationPriority, txAmpNotificationState }
            STATUS current
            DESCRIPTION 
                "Indicates a fault if the amplifier detects an internal fault at power ON. 
                If other faults are indicated at the same time, the cause of these 
                faults must be rectified first. If the InitFail fault still exists after 
                other faults have been rectified, the amplifier must be replaced. 
                
                Possible values:
                off(2)
                fault(3) -  the amplifier detects an internal fault at power ON
                
                Notification class: warning"
            ::= { rsXx9TxNotifications 10014 }

        
        txAmpAbsorberFail NOTIFICATION-TYPE
            OBJECTS { commonNotificationAlarmClass, txAmpNotificationPriority, txAmpNotificationState }
            STATUS current
            DESCRIPTION 
                "This warning is shown if overheating of a rack absorber is detected. 
                Normally, this warning is signaled by all amplifiers of a transmitter 
                simultaneously. If the warning is signaled by only one amplifier, 
                check the rack wiring.
                
                Possible values:
                off(2)
                warning(4) -  overheating of a rack absorber is detected
                
                Notification class: warning"
            ::= { rsXx9TxNotifications 10015 }

        
        txAmpOn NOTIFICATION-TYPE
            OBJECTS { commonNotificationAlarmClass, txAmpNotificationPriority, txAmpNotificationState }
            STATUS current
            DESCRIPTION 
                "Indicates whether the amplifier has been switched on or off.
                
                Possible values:
                off(2)
                ok(5)
                
                Notification class: fault"
            ::= { rsXx9TxNotifications 10016 }

        
        txAmpBlocking NOTIFICATION-TYPE
            OBJECTS { commonNotificationAlarmClass, txAmpNotificationPriority, txAmpNotificationState }
            STATUS current
            DESCRIPTION 
                "
                
                Possible values:
                off(2)
                fault(3)
                
                Notification class: fault"
            ::= { rsXx9TxNotifications 10017 }

        
        txSwiCoSummary NOTIFICATION-TYPE
            OBJECTS { commonNotificationAlarmClass, txSwiCoNotificationPriority, txSwiCoNotificationState }
            STATUS current
            DESCRIPTION 
                "shows state of Switchless Combiner
                Possible values:
                off(2)
                warn(4)
                ok(5)
                
                Notification class: fault"
            ::= { rsXx9TxNotifications 11000 }

        
        txSwiCoHwLink NOTIFICATION-TYPE
            STATUS current
            DESCRIPTION 
                "Indicates whether there are data communications between the 
                transmitter and switchless combiner.
                
                Possible values:
                off(2) - no connection to RCB
                warn(4) - no connection to potentiometer
                ok(5) - OK
                
                Notification class: warning"
            ::= { rsXx9TxNotifications 11001 }

        
        txSwiCoHwWarn NOTIFICATION-TYPE
            STATUS current
            DESCRIPTION 
                "Indicates whether the switchless combiner signals a warning. This 
                indication is identical to the indication on the control panel of the 
                switchless combiner.
                
                Possible values:
                off(2) - no connection to RCB
                warn(4) - no connection to potentiometer
                ok(5) - OK
                
                Notification class: warning"
            ::= { rsXx9TxNotifications 11002 }

        
        txSwiCoHwFault NOTIFICATION-TYPE
            STATUS current
            DESCRIPTION 
                "Indicates whether the switchless combiner signals an error. This 
                indication is identical to the indication on the control panel of the 
                switchless combiner.
                
                Possible values:
                off(2) - no connection to RCB
                warn(4) - no connection to potentiometer
                ok(5) - OK
                
                Notification class: warning"
            ::= { rsXx9TxNotifications 11003 }

        
        txSwiCoHwLocal NOTIFICATION-TYPE
            STATUS current
            DESCRIPTION 
                "Indicates whether the switchless combiner is in Local mode or Remote mode. 
                For the control to work, the switchless combiner has to be in Remote mode. 
                
                Possible values:
                off(2) - no connection to RCB
                warn(4) - switchless combiner in local state
                ok(5) - OK, switchless combiner in remote state
                
                Notification class: warning"
            ::= { rsXx9TxNotifications 11004 }

        
        txSwiCoRcbFail NOTIFICATION-TYPE
            OBJECTS { commonNotificationAlarmClass, txSwiCoNotificationPriority, txSwiCoNotificationState }
            STATUS current
            DESCRIPTION 
                "Indicates whether the redundancy control board in the TCE900 system 
                control functions without errors.
                
                Possible values:
                fault(3)
                warning(4)
                ok(5)
                
                Notification class: warning"
            ::= { rsXx9TxNotifications 11005 }

        
        txSwiCoRfProbeFail NOTIFICATION-TYPE
            OBJECTS { commonNotificationAlarmClass, txSwiCoNotificationPriority, txSwiCoNotificationState }
            STATUS current
            DESCRIPTION 
                "Indicates whether the test point at the antenna output functions.
                
                Possible values:
                fault(3)
                warning(4) - warning or no link
                ok(5)
                
                Notification class: warning"
            ::= { rsXx9TxNotifications 11006 }

        
        txSwiCoRegulationSummary NOTIFICATION-TYPE
            OBJECTS { commonNotificationAlarmClass, txSwiCoNotificationPriority, txSwiCoNotificationState }
            STATUS current
            DESCRIPTION 
                "shows the regulation state of Switchless Combiner
                Possible values:
                fault(3)
                warning(4) - warning or no link
                ok(5)
                
                Notification class: warning"
            ::= { rsXx9TxNotifications 11007 }

        
        txRfSensorLinkStatus NOTIFICATION-TYPE
            OBJECTS { commonNotificationAlarmClass, txTransmitterNotificationPriority, txTransmitterNotificationState }
            STATUS current
            DESCRIPTION 
                "A communication fault to RF Sensor is detected. 
                The CAN bus connection between sensor and 
                TCE900 should be checked.
                
                Possible values:
                fault(3) - not connected
                ok(5) - ok
                
                Notification class: warning"
            ::= { rsXx9TxNotifications 12000 }

        
        txRfSensorCalibrated NOTIFICATION-TYPE
            STATUS current
            DESCRIPTION 
                "The RF sensor is not calibrated. In multi-standard transmitters 
                the rf sensor has to be calibrated for each tv standard seperately"
            ::= { rsXx9TxNotifications 12001 }

        
        rsXx9TxObjects OBJECT IDENTIFIER ::= { rsXx9Tx 1 }

        
        txTransmitter OBJECT IDENTIFIER ::= { rsXx9TxObjects 1 }

        
        txTransmitterNotificationTable OBJECT-TYPE
            SYNTAX SEQUENCE OF TxTransmitterNotificationEntry
            MAX-ACCESS not-accessible
            STATUS current
            DESCRIPTION
                "The context information/configuration for the
                general transmitter status notifications."
            ::= { txTransmitter 1 }

        
        txTransmitterNotificationEntry OBJECT-TYPE
            SYNTAX TxTransmitterNotificationEntry
            MAX-ACCESS not-accessible
            STATUS current
            DESCRIPTION
                "An entry in the txGeneralNotificationTable."
            INDEX { txTransmitterNotificationTxIdx, txTransmitterNotificationIdx }
            ::= { txTransmitterNotificationTable 1 }

        
        TxTransmitterNotificationEntry ::=
            SEQUENCE { 
                txTransmitterNotificationTxIdx
                    IndexTransmitter,
                txTransmitterNotificationIdx
                    Unsigned32,
                txTransmitterNotificationName
                    INTEGER,
                txTransmitterNotificationMask
                    NotificationMask,
                txTransmitterNotificationPriority
                    NotificationPriority,
                txTransmitterNotificationState
                    NotificationState
             }

        txTransmitterNotificationTxIdx OBJECT-TYPE
            SYNTAX IndexTransmitter
            MAX-ACCESS not-accessible
            STATUS current
            DESCRIPTION
                "The transmitter index."
            ::= { txTransmitterNotificationEntry 1 }

        
        txTransmitterNotificationIdx OBJECT-TYPE
            SYNTAX Unsigned32 (1..10 | 1000..1004 | 1500..1504)
            MAX-ACCESS not-accessible
            STATUS current
            DESCRIPTION
                "The notification number as below rsXx9TxNotifications.
                This is a helper column and therefore not-accessible."
            ::= { txTransmitterNotificationEntry 2 }

        
        txTransmitterNotificationName OBJECT-TYPE
            SYNTAX INTEGER
                {
                txSummary(1),
                txRF(2),
                txReflection(3),
                txRfSensorSummary(4),
                txLocal(5),
                txExciterAutomaticOn(6),
                txExciterAutomaticReady(7),
                txExciterAutomaticSwitchedOver(8),
                txExciterAutomaticRfSwitchSummary(9),
                txExciterAutomaticSummary(10),
                txActiveReserveExcAutoOn(1000),
                txActiveReserveExcAutoReady(1001),
                txActiveReserveExcAutoSwitchedOver(1002),
                txActiveReserveExcAutoRfSwitchSummary(1003),
                txActiveReserveExcAutoSummary(1004),
                txActiveReserveOstAutoOn(1500),
                txActiveReserveOstAutoReady(1501),
                txActiveReserveOstAutoSwitchedOver(1502),
                txActiveReserveOstAutoRfSwitchSummary(1503),
                txActiveReserveOstAutoSummary(1504)
                }
            MAX-ACCESS read-only
            STATUS current
            DESCRIPTION
                "The notification number as an enumeration.
                The enumeration correlates with the notifications under rsXx9TxNotifications."
            ::= { txTransmitterNotificationEntry 3 }

        
        txTransmitterNotificationMask OBJECT-TYPE
            SYNTAX NotificationMask
            MAX-ACCESS read-write
            STATUS current
            DESCRIPTION
                "See textual convention for details."
            ::= { txTransmitterNotificationEntry 4 }

        
        txTransmitterNotificationPriority OBJECT-TYPE
            SYNTAX NotificationPriority
            MAX-ACCESS read-write
            STATUS current
            DESCRIPTION
                "See textual convention for details."
            ::= { txTransmitterNotificationEntry 5 }

        
        txTransmitterNotificationState OBJECT-TYPE
            SYNTAX NotificationState
            MAX-ACCESS read-only
            STATUS current
            DESCRIPTION
                "See textual convention for details."
            ::= { txTransmitterNotificationEntry 6 }

        
        txTransmitterCommandsTable OBJECT-TYPE
            SYNTAX SEQUENCE OF TxTransmitterCommandsEntry
            MAX-ACCESS not-accessible
            STATUS current
            DESCRIPTION
                "General transmitter settings."
            ::= { txTransmitter 2 }

        
        txTransmitterCommandsEntry OBJECT-TYPE
            SYNTAX TxTransmitterCommandsEntry
            MAX-ACCESS not-accessible
            STATUS current
            DESCRIPTION
                "An entry in the txGeneralCommandsTable table."
            INDEX { txTransmitterNotificationTxIdx }
            ::= { txTransmitterCommandsTable 1 }

        
        TxTransmitterCommandsEntry ::=
            SEQUENCE { 
                txTransCmdReset
                    Trigger,
                txTransCmdOperationMode
                    SwitchOnOff,
                txTransCmdNominalPower
                    Unsigned32,
                txTransCmdReserveOpMode
                    SwitchOnOff,
                txTransCmdChangeModulation
                    Xx9ModulationMode,
                txTransCmdReflectionCheck
                    INTEGER,
                txTransCmdPrgOnAfterSumFault
                    TruthValue,
                txTransCmdWarnOnDohertyMismatch
                    SwitchOnOff
             }

        txTransCmdReset OBJECT-TYPE
            SYNTAX Trigger
            MAX-ACCESS read-write
            STATUS current
            DESCRIPTION
                "Switch used to reset all faults stored in the transmitter. 
                Stored faults are: Reflection Fail. Resetting stored faults can cause 
                automatic redundancy functions, which are currently in the 
                switched-over state, to switch back to their original preselected state.
                "
            ::= { txTransmitterCommandsEntry 1 }

        
        txTransCmdOperationMode OBJECT-TYPE
            SYNTAX SwitchOnOff
            MAX-ACCESS read-write
            STATUS current
            DESCRIPTION
                "Switch used to switch the components in the program path of the 
                transmitter on and off.
                "
            ::= { txTransmitterCommandsEntry 2 }

        
        txTransCmdNominalPower OBJECT-TYPE
            SYNTAX Unsigned32
            UNITS "milli W"
            MAX-ACCESS read-write
            STATUS current
            DESCRIPTION
                "The nominal power of the transmitter must be set here. 
                The nominal power is defined by the number and type of 
                amplifiers as well as by the used TV standard.
                "
            ::= { txTransmitterCommandsEntry 3 }

        
        txTransCmdReserveOpMode OBJECT-TYPE
            SYNTAX SwitchOnOff
            MAX-ACCESS read-write
            STATUS current
            DESCRIPTION
                "Switch used to switch all components in the standby path of the 
                transmitter on and off. 
                (standby exciter with 'dual drive' redundancy concept and standby 
                output stage with 'active PA Reserve' redundancy concept).
                "
            ::= { txTransmitterCommandsEntry 4 }

        
        txTransCmdChangeModulation OBJECT-TYPE
            SYNTAX Xx9ModulationMode
            MAX-ACCESS read-write
            STATUS current
            DESCRIPTION
                "Changes the modulation mode of the transmitter (without rebootint).
                Get requests will return none(2). 
                A Set request with the desired modulation mode does trigger a modulation mode switch.
                A modulation mode switch does only happen, if the mode is switching to one of the
                preconfigured modulation modes (txTransStPrimaryModMode or txTransStPrimaryModMode). "
            ::= { txTransmitterCommandsEntry 5 }

        
        txTransCmdReflectionCheck OBJECT-TYPE
            SYNTAX INTEGER
                {
                keepRfOff(1),
                checkThreeTimes(2)
                }
            MAX-ACCESS read-write
            STATUS current
            DESCRIPTION
                "Description."
            ::= { txTransmitterCommandsEntry 6 }

        
        txTransCmdPrgOnAfterSumFault OBJECT-TYPE
            SYNTAX TruthValue
            MAX-ACCESS read-write
            STATUS current
            DESCRIPTION
                "Description."
            ::= { txTransmitterCommandsEntry 7 }

        
        txTransCmdWarnOnDohertyMismatch OBJECT-TYPE
            SYNTAX SwitchOnOff
            MAX-ACCESS read-write
            STATUS current
            DESCRIPTION
                "Description.
                
                only has an effect on transmitters with doherty amplifiers."
            ::= { txTransmitterCommandsEntry 8 }

        
        txTransmitterStateTable OBJECT-TYPE
            SYNTAX SEQUENCE OF TxTransmitterStateEntry
            MAX-ACCESS not-accessible
            STATUS current
            DESCRIPTION
                "General transmitter status."
            ::= { txTransmitter 3 }

        
        txTransmitterStateEntry OBJECT-TYPE
            SYNTAX TxTransmitterStateEntry
            MAX-ACCESS not-accessible
            STATUS current
            DESCRIPTION
                "An entry in the txTransmitterStateTable."
            INDEX { txTransmitterNotificationTxIdx }
            ::= { txTransmitterStateTable 1 }

        
        TxTransmitterStateEntry ::=
            SEQUENCE { 
                txTransStForwardPower
                    Unsigned32,
                txTransStReflectedPower
                    Unsigned32,
                txTransStModulationMode
                    Xx9ModulationMode,
                txTransStPrimaryModMode
                    Xx9ModulationMode,
                txTransStSecondaryModMode
                    Xx9ModulationMode,
                txTransStPaEfficiency
                    Integer32
             }

        txTransStForwardPower OBJECT-TYPE
            SYNTAX Unsigned32
            UNITS "milli W"
            MAX-ACCESS read-only
            STATUS current
            DESCRIPTION
                "Forward power of the transmitter."
            ::= { txTransmitterStateEntry 1 }

        
        txTransStReflectedPower OBJECT-TYPE
            SYNTAX Unsigned32
            UNITS "milli W"
            MAX-ACCESS read-only
            STATUS current
            DESCRIPTION
                "Reflected power of the transmitter."
            ::= { txTransmitterStateEntry 2 }

        
        txTransStModulationMode OBJECT-TYPE
            SYNTAX Xx9ModulationMode
            MAX-ACCESS read-only
            STATUS current
            DESCRIPTION
                "Modulation mode of the transmitter."
            ::= { txTransmitterStateEntry 3 }

        
        txTransStPrimaryModMode OBJECT-TYPE
            SYNTAX Xx9ModulationMode
            MAX-ACCESS read-only
            STATUS current
            DESCRIPTION
                "Configured primary modulation mode of the transmitter."
            ::= { txTransmitterStateEntry 4 }

        
        txTransStSecondaryModMode OBJECT-TYPE
            SYNTAX Xx9ModulationMode
            MAX-ACCESS read-only
            STATUS current
            DESCRIPTION
                "Configured secondary modulation mode of the transmitter."
            ::= { txTransmitterStateEntry 5 }

        
        txTransStPaEfficiency OBJECT-TYPE
            SYNTAX Integer32 (-999..999)
            UNITS "per mille"
            MAX-ACCESS read-only
            STATUS current
            DESCRIPTION
                "Shows efficiency of all amplifiers 
                (including loss of combiners 
                but without power consumption of 
                TCE900 and cooling system)
                
                values <0 are invalid, because 
                PA-efficiency could not be calculated"
            ::= { txTransmitterStateEntry 6 }

        
        txExciterAutomaticTable OBJECT-TYPE
            SYNTAX SEQUENCE OF TxExciterAutomaticEntry
            MAX-ACCESS not-accessible
            STATUS current
            DESCRIPTION
                "Exciter automatic configuration and status."
            ::= { txTransmitter 4 }

        
        txExciterAutomaticEntry OBJECT-TYPE
            SYNTAX TxExciterAutomaticEntry
            MAX-ACCESS not-accessible
            STATUS current
            DESCRIPTION
                "An entry in the txExciterAutomaticTable."
            INDEX { txTransmitterNotificationTxIdx }
            ::= { txExciterAutomaticTable 1 }

        
        TxExciterAutomaticEntry ::=
            SEQUENCE { 
                txExcAutoOperationMode
                    SwitchOnOff,
                txExciterAutomaticMode
                    AutomaticMode,
                txExcAutoGuardTime
                    Unsigned32,
                txExcAutoPreselectExcA
                    Trigger,
                txExcAutoPreselectExcB
                    Trigger,
                txExcAutoPreselected
                    IndexAB,
                txExcAutoRfSwitchPosition
                    IndexAB
             }

        txExcAutoOperationMode OBJECT-TYPE
            SYNTAX SwitchOnOff
            MAX-ACCESS read-write
            STATUS current
            DESCRIPTION
                "Switches the automatic exciter switchover on and off. "
            ::= { txExciterAutomaticEntry 1 }

        
        txExciterAutomaticMode OBJECT-TYPE
            SYNTAX AutomaticMode
            MAX-ACCESS read-write
            STATUS current
            DESCRIPTION
                "Determines the behavior after successfully switching over to a 
                standby exciter. 
                
                singleShot(2)   - The selector of the automatic exciter switchover 
                remains fixed on the standby exciter until either the preselection 
                of the exciter is pressed again or the 'Reset Faults Transmitter' 
                button is pressed. 
                severalTimes(1) - The automatic switchover automatically switches 
                back to the preselected exciter as soon as the standby exciter 
                signals an error and the preselected exciter is operational again.
                "
            ::= { txExciterAutomaticEntry 2 }

        
        txExcAutoGuardTime OBJECT-TYPE
            SYNTAX Unsigned32 (1..60)
            UNITS "second"
            MAX-ACCESS read-write
            STATUS current
            DESCRIPTION
                "Indicates the configured checkout time which must elapse before 
                being able to switch to another exciter. This can be used to make 
                sure that short-term errors do not immediately cause a switchover. 
                The Guard Time is also effective for switching over to the 
                preselected exciter in the 'Multiple Switch' switch mode. The 
                setting can be changed here.
                "
            ::= { txExciterAutomaticEntry 3 }

        
        txExcAutoPreselectExcA OBJECT-TYPE
            SYNTAX Trigger
            MAX-ACCESS read-write
            STATUS current
            DESCRIPTION
                "Preselect exciter A."
            ::= { txExciterAutomaticEntry 4 }

        
        txExcAutoPreselectExcB OBJECT-TYPE
            SYNTAX Trigger
            MAX-ACCESS read-write
            STATUS current
            DESCRIPTION
                "Preselect exciter B."
            ::= { txExciterAutomaticEntry 5 }

        
        txExcAutoPreselected OBJECT-TYPE
            SYNTAX IndexAB
            MAX-ACCESS read-only
            STATUS current
            DESCRIPTION
                "The preselected exciter.
                
                Indicates which exciter has been preselected for operation. 
                If the 'Switch Mode' of the automatic switchover function is 
                configured to 'Single Switch' and the exciter switched over, 
                the switchover can be undone by selecting the preselected 
                exciter again.
                "
            ::= { txExciterAutomaticEntry 6 }

        
        txExcAutoRfSwitchPosition OBJECT-TYPE
            SYNTAX IndexAB
            MAX-ACCESS read-only
            STATUS current
            DESCRIPTION
                "The active exciter."
            ::= { txExciterAutomaticEntry 7 }

        
        txActiveReserve OBJECT IDENTIFIER ::= { txTransmitter 5 }

        
        txActiveReserveExciterTable OBJECT-TYPE
            SYNTAX SEQUENCE OF TxActiveReserveExciterEntry
            MAX-ACCESS not-accessible
            STATUS current
            DESCRIPTION
                "Description."
            ::= { txActiveReserve 1 }

        
        txActiveReserveExciterEntry OBJECT-TYPE
            SYNTAX TxActiveReserveExciterEntry
            MAX-ACCESS not-accessible
            STATUS current
            DESCRIPTION
                "Description."
            INDEX { txTransmitterNotificationTxIdx }
            ::= { txActiveReserveExciterTable 1 }

        
        TxActiveReserveExciterEntry ::=
            SEQUENCE { 
                txArExcAutomaticOperationMode
                    SwitchOnOff,
                txArExcAutomaticMode
                    AutomaticMode,
                txArExcAutomaticGuardTime
                    Unsigned32,
                txArPreselectExcA
                    Trigger,
                txArPreselectExcB
                    Trigger,
                txArExcPreselected
                    IndexAB,
                txArExcSelected
                    INTEGER
             }

        txArExcAutomaticOperationMode OBJECT-TYPE
            SYNTAX SwitchOnOff
            MAX-ACCESS read-write
            STATUS current
            DESCRIPTION
                "Switches the automatic exciter switchover on and off. "
            ::= { txActiveReserveExciterEntry 1 }

        
        txArExcAutomaticMode OBJECT-TYPE
            SYNTAX AutomaticMode
            MAX-ACCESS read-write
            STATUS current
            DESCRIPTION
                "Determines the behavior after successfully switching over to a 
                standby exciter. 
                
                singleShot(2)   - The automatic exciter switchover selector remains 
                fixed to the standby exciter until the 'Recommend Selection' button 
                is pressed. 
                severalTimes(1) - The automatic switchover automatically switches 
                back to the preselected exciter as soon as the standby exciter 
                signals an error and the preselected exciter is operational again.
                "
            ::= { txActiveReserveExciterEntry 2 }

        
        txArExcAutomaticGuardTime OBJECT-TYPE
            SYNTAX Unsigned32 (1..60)
            UNITS "second"
            MAX-ACCESS read-write
            STATUS current
            DESCRIPTION
                "Indicates the configured checkout time which must elapse before 
                being able to switch to another exciter. This can be used to make 
                sure that short-term errors do not immediately cause a switchover. 
                The Guard Time is also effective for switching over to the preselected 
                exciter in the 'Multiple Switch' switch mode. The setting can be 
                changed here."
            ::= { txActiveReserveExciterEntry 3 }

        
        txArPreselectExcA OBJECT-TYPE
            SYNTAX Trigger
            MAX-ACCESS read-write
            STATUS current
            DESCRIPTION
                "Description."
            ::= { txActiveReserveExciterEntry 4 }

        
        txArPreselectExcB OBJECT-TYPE
            SYNTAX Trigger
            MAX-ACCESS read-write
            STATUS current
            DESCRIPTION
                "Description."
            ::= { txActiveReserveExciterEntry 5 }

        
        txArExcPreselected OBJECT-TYPE
            SYNTAX IndexAB
            MAX-ACCESS read-only
            STATUS current
            DESCRIPTION
                "Indicates which exciter has been preselected for operation. 
                The setting can be changed here. If the 'Switch Mode' of the 
                automatic switchover function is configured to 'Single Switch' 
                and the exciter switched over, the switchover can be undone 
                by selecting the preselected exciter again.
                "
            ::= { txActiveReserveExciterEntry 6 }

        
        txArExcSelected OBJECT-TYPE
            SYNTAX INTEGER
                {
                exciterA(1),
                exciterB(2),
                undefined(3)
                }
            MAX-ACCESS read-only
            STATUS current
            DESCRIPTION
                "Indicates which exciter is currently active, i.e. is working on the 
                antenna depending on the switch state of the automatic exciter 
                switchover.
                "
            ::= { txActiveReserveExciterEntry 7 }

        
        txActiveReserveOstTable OBJECT-TYPE
            SYNTAX SEQUENCE OF TxActiveReserveOstEntry
            MAX-ACCESS not-accessible
            STATUS current
            DESCRIPTION
                "Description."
            ::= { txActiveReserve 2 }

        
        txActiveReserveOstEntry OBJECT-TYPE
            SYNTAX TxActiveReserveOstEntry
            MAX-ACCESS not-accessible
            STATUS current
            DESCRIPTION
                "Description."
            INDEX { txTransmitterNotificationTxIdx }
            ::= { txActiveReserveOstTable 1 }

        
        TxActiveReserveOstEntry ::=
            SEQUENCE { 
                txArOstAutomaticOperationMode
                    SwitchOnOff,
                txArOstAutomaticMode
                    AutomaticMode,
                txArOstAutomaticGuardTime
                    Unsigned32,
                txArPreselectOstAOstBtoAnt
                    Trigger,
                txArPreselectOstAOstBtoDl
                    Trigger,
                txArPreselectOstAtoAntOstBtoDl
                    Trigger,
                txArPreselectOstAtoDlOstBtoAnt
                    Trigger,
                txArOstPreselected
                    INTEGER,
                txArOstSelected
                    INTEGER
             }

        txArOstAutomaticOperationMode OBJECT-TYPE
            SYNTAX SwitchOnOff
            MAX-ACCESS read-write
            STATUS current
            DESCRIPTION
                "Switches on and off the output-stage switchover function. "
            ::= { txActiveReserveOstEntry 1 }

        
        txArOstAutomaticMode OBJECT-TYPE
            SYNTAX AutomaticMode
            MAX-ACCESS read-write
            STATUS current
            DESCRIPTION
                "Determines the behavior after successfully removing an output 
                stage from the signal path. 
                
                singleShot(2)   - The output stage switch remains permanently fixed 
                in the new position until either the configuration of the output stage 
                is reset or until the 'Reset Faults Transmitter' button is pressed. 
                severalTimes(1) - The automatic switchover function automatically 
                switches the formerly defective output stage back into the signal path.
                "
            ::= { txActiveReserveOstEntry 2 }

        
        txArOstAutomaticGuardTime OBJECT-TYPE
            SYNTAX Unsigned32 (1..60)
            UNITS "second"
            MAX-ACCESS read-write
            STATUS current
            DESCRIPTION
                "Indicates the configured checkout time which must elapse 
                before an output stage is removed from the signal path. 
                This can be used to make sure that short-term errors do 
                not cause toggling. The Guard Time is also effective in the 
                'Multiple Switch' switch mode for switching over to the 
                preselected configuration of the output stages. The setting 
                can be changed here.
                "
            ::= { txActiveReserveOstEntry 3 }

        
        txArPreselectOstAOstBtoAnt OBJECT-TYPE
            SYNTAX Trigger
            MAX-ACCESS read-write
            STATUS current
            DESCRIPTION
                "Description."
            ::= { txActiveReserveOstEntry 4 }

        
        txArPreselectOstAOstBtoDl OBJECT-TYPE
            SYNTAX Trigger
            MAX-ACCESS read-write
            STATUS current
            DESCRIPTION
                "Description."
            ::= { txActiveReserveOstEntry 5 }

        
        txArPreselectOstAtoAntOstBtoDl OBJECT-TYPE
            SYNTAX Trigger
            MAX-ACCESS read-write
            STATUS current
            DESCRIPTION
                "Description."
            ::= { txActiveReserveOstEntry 6 }

        
        txArPreselectOstAtoDlOstBtoAnt OBJECT-TYPE
            SYNTAX Trigger
            MAX-ACCESS read-write
            STATUS current
            DESCRIPTION
                "Description."
            ::= { txActiveReserveOstEntry 7 }

        
        txArOstPreselected OBJECT-TYPE
            SYNTAX INTEGER
                {
                ostAandOstBtoAntenna(1),
                ostAandOstBtoDummyload(2),
                ostAtoAntennaAndOstBtoDummyload(3),
                ostAtoDummyloadAndOstBtoAntenna(4)
                }
            MAX-ACCESS read-only
            STATUS current
            DESCRIPTION
                "Indicates how the two Output Stages A and B are to be 
                interconnected to each other."
            ::= { txActiveReserveOstEntry 8 }

        
        txArOstSelected OBJECT-TYPE
            SYNTAX INTEGER
                {
                ostAandOstBtoAntenna(1),
                ostAandOstBtoDummyload(2),
                ostAtoAntennaAndOstBtoDummyload(3),
                ostAtoDummyloadAndOstBtoAntenna(4),
                undefined(5)
                }
            MAX-ACCESS read-only
            STATUS current
            DESCRIPTION
                "
                5=Undefined, 
                1=Ost A+B->Ant, 
                2=A+B->DL, 
                3=A->Ant /B->DL, 
                4=B->Ant /A->DL
                "
            ::= { txActiveReserveOstEntry 9 }

        
        txExciter OBJECT IDENTIFIER ::= { rsXx9TxObjects 2 }

        
        txExciterNotificationTable OBJECT-TYPE
            SYNTAX SEQUENCE OF TxExciterNotificationEntry
            MAX-ACCESS not-accessible
            STATUS current
            DESCRIPTION
                "The context information/configuration for the
                exciter status notifications."
            ::= { txExciter 1 }

        
        txExciterNotificationEntry OBJECT-TYPE
            SYNTAX TxExciterNotificationEntry
            MAX-ACCESS not-accessible
            STATUS current
            DESCRIPTION
                "An entry in the txExciterNotificationTable."
            INDEX { txExciterNotificationTxIdx, txExciterNotificationExcIdx, txExciterNotificationIdx }
            ::= { txExciterNotificationTable 1 }

        
        TxExciterNotificationEntry ::=
            SEQUENCE { 
                txExciterNotificationTxIdx
                    IndexTransmitter,
                txExciterNotificationExcIdx
                    IndexAB,
                txExciterNotificationIdx
                    Unsigned32,
                txExciterNotificationName
                    INTEGER,
                txExciterNotificationMask
                    NotificationMask,
                txExciterNotificationPriority
                    NotificationPriority,
                txExciterNotificationState
                    NotificationState
             }

        txExciterNotificationTxIdx OBJECT-TYPE
            SYNTAX IndexTransmitter
            MAX-ACCESS not-accessible
            STATUS current
            DESCRIPTION
                "The transmitter index."
            ::= { txExciterNotificationEntry 1 }

        
        txExciterNotificationExcIdx OBJECT-TYPE
            SYNTAX IndexAB
            MAX-ACCESS not-accessible
            STATUS current
            DESCRIPTION
                "This index distinguishes the exiters.
                Necessary if you have dual drive transmitters."
            ::= { txExciterNotificationEntry 2 }

        
        txExciterNotificationIdx OBJECT-TYPE
            SYNTAX Unsigned32 (2000..2004)
            MAX-ACCESS not-accessible
            STATUS current
            DESCRIPTION
                "The notification number as below rsXx9TxNotifications.
                This is a helper column and therefore not-accessible."
            ::= { txExciterNotificationEntry 3 }

        
        txExciterNotificationName OBJECT-TYPE
            SYNTAX INTEGER
                {
                txExciterSummary(2000),
                txExciterLoop(2001),
                txExciterMute(2002),
                txExciterOutputConnect(2003),
                txExciterRfState(2004)
                }
            MAX-ACCESS read-only
            STATUS current
            DESCRIPTION
                "The notification number as an enumeration.
                The enumeration correlates with the notifications under rsXx9TxNotifications."
            ::= { txExciterNotificationEntry 4 }

        
        txExciterNotificationMask OBJECT-TYPE
            SYNTAX NotificationMask
            MAX-ACCESS read-write
            STATUS current
            DESCRIPTION
                "See textual convention for details."
            ::= { txExciterNotificationEntry 5 }

        
        txExciterNotificationPriority OBJECT-TYPE
            SYNTAX NotificationPriority
            MAX-ACCESS read-write
            STATUS current
            DESCRIPTION
                "See textual convention for details."
            ::= { txExciterNotificationEntry 6 }

        
        txExciterNotificationState OBJECT-TYPE
            SYNTAX NotificationState
            MAX-ACCESS read-only
            STATUS current
            DESCRIPTION
                "See textual convention for details."
            ::= { txExciterNotificationEntry 7 }

        
        txExciterCommandsTable OBJECT-TYPE
            SYNTAX SEQUENCE OF TxExciterCommandsEntry
            MAX-ACCESS not-accessible
            STATUS current
            DESCRIPTION
                "Exciter settings."
            ::= { txExciter 2 }

        
        txExciterCommandsEntry OBJECT-TYPE
            SYNTAX TxExciterCommandsEntry
            MAX-ACCESS not-accessible
            STATUS current
            DESCRIPTION
                "An entry in the txExciterCommandsTable."
            INDEX { txExciterNotificationTxIdx, txExciterNotificationExcIdx }
            ::= { txExciterCommandsTable 1 }

        
        TxExciterCommandsEntry ::=
            SEQUENCE { 
                txExcCmdFrequency
                    Unsigned32,
                txExcCmdModulationMode
                    Xx9ModulationMode,
                txExcCmdRfSlope
                    Integer32,
                txExcCmdOutputAttenuation
                    INTEGER,
                txExcCmdLoopControl
                    INTEGER,
                txExcCmdOperationMode
                    SwitchOnOff
             }

        txExcCmdFrequency OBJECT-TYPE
            SYNTAX Unsigned32 (87500000..108000000 | 160000000..870000000)
            UNITS "Hz"
            MAX-ACCESS read-write
            STATUS current
            DESCRIPTION
                "The transmitter frequency.
                Its interpretation is modulation dependent:
                DVB-T, DVB-T2, DTMB, DAB, ISDB-T - channel center frequency
                ATSC - pilot carrier frequency
                ATV  - video carrier frequency
                FM   - carrier frequency
                
                For band II transmitters the range is 87500000 - 108000000 Hz.
                For all other transmitters the range is 160000000 - 870000000 Hz."
            ::= { txExciterCommandsEntry 1 }

        
        txExcCmdModulationMode OBJECT-TYPE
            SYNTAX Xx9ModulationMode
            MAX-ACCESS read-only
            STATUS current
            DESCRIPTION
                "Modulation mode of the exciter."
            ::= { txExciterCommandsEntry 2 }

        
        txExcCmdRfSlope OBJECT-TYPE
            SYNTAX Integer32 (-20..20)
            UNITS "centi Bel"
            MAX-ACCESS read-write
            STATUS current
            DESCRIPTION
                "Corrects a slope in amplitude spectrum.
                
                Not for band 2."
            ::= { txExciterCommandsEntry 3 }

        
        txExcCmdOutputAttenuation OBJECT-TYPE
            SYNTAX INTEGER
                {
                dB0(1),
                dB3(2),
                dB6(3),
                dB9(4)
                }
            MAX-ACCESS read-write
            STATUS current
            DESCRIPTION
                "Used to attenuate the RF level of exciter up to 9dB:
                dB0(1) - 0 dB
                dB3(2) - 3 dB
                dB6(3) - 6 dB
                dB9(4) - 9 dB"
            ::= { txExciterCommandsEntry 4 }

        
        txExcCmdLoopControl OBJECT-TYPE
            SYNTAX INTEGER
                {
                limited(1),
                full(2)
                }
            MAX-ACCESS read-write
            STATUS current
            DESCRIPTION
                "Description."
            ::= { txExciterCommandsEntry 5 }

        
        txExcCmdOperationMode OBJECT-TYPE
            SYNTAX SwitchOnOff
            MAX-ACCESS read-write
            STATUS current
            DESCRIPTION
                "Switch used to switch the exciter on and off.
                Directly affects the output of the exciter.
                Use this command only in exciter-only configuration (no TxControl available).
                misuse might lead to hardware damage.
                For changing the operationMode of an exciter within a transmitter,
                always prefer txTransCmdOperationMode over txExcCmdOperationMode.
                "
            ::= { txExciterCommandsEntry 6 }

        
        txExciterStateTable OBJECT-TYPE
            SYNTAX SEQUENCE OF TxExciterStateEntry
            MAX-ACCESS not-accessible
            STATUS current
            DESCRIPTION
                "Exciter status."
            ::= { txExciter 3 }

        
        txExciterStateEntry OBJECT-TYPE
            SYNTAX TxExciterStateEntry
            MAX-ACCESS not-accessible
            STATUS current
            DESCRIPTION
                "An entry in the txExciterStateTable."
            INDEX { txExciterNotificationTxIdx, txExciterNotificationExcIdx }
            ::= { txExciterStateTable 1 }

        
        TxExciterStateEntry ::=
            SEQUENCE { 
                txExcStOperationOn
                    TruthValue
             }

        txExcStOperationOn OBJECT-TYPE
            SYNTAX TruthValue
            MAX-ACCESS read-only
            STATUS current
            DESCRIPTION
                "State of exciter operation mode:
                true(1)  - on
                false(2) - off"
            ::= { txExciterStateEntry 1 }

        
        txInputInterfaces OBJECT IDENTIFIER ::= { rsXx9TxObjects 3 }

        
        txInpIfNotificationTable OBJECT-TYPE
            SYNTAX SEQUENCE OF TxInpIfNotificationEntry
            MAX-ACCESS not-accessible
            STATUS current
            DESCRIPTION
                "The context information/configuration for the
                input interface status notifications."
            ::= { txInputInterfaces 1 }

        
        txInpIfNotificationEntry OBJECT-TYPE
            SYNTAX TxInpIfNotificationEntry
            MAX-ACCESS not-accessible
            STATUS current
            DESCRIPTION
                "An entry in the txInpIfNotificationTable."
            INDEX { txInpIfNotificationTxIdx, txInpIfNotificationExcIdx, txInpIfNotificationInputIdx, txInpIfNotificationIdx }
            ::= { txInpIfNotificationTable 1 }

        
        TxInpIfNotificationEntry ::=
            SEQUENCE { 
                txInpIfNotificationTxIdx
                    IndexTransmitter,
                txInpIfNotificationExcIdx
                    IndexAB,
                txInpIfNotificationInputIdx
                    INTEGER,
                txInpIfNotificationIdx
                    Unsigned32,
                txInpIfNotificationName
                    INTEGER,
                txInpIfNotificationMask
                    NotificationMask,
                txInpIfNotificationPriority
                    NotificationPriority,
                txInpIfNotificationState
                    NotificationState
             }

        txInpIfNotificationTxIdx OBJECT-TYPE
            SYNTAX IndexTransmitter
            MAX-ACCESS not-accessible
            STATUS current
            DESCRIPTION
                "The transmitter index."
            ::= { txInpIfNotificationEntry 1 }

        
        txInpIfNotificationExcIdx OBJECT-TYPE
            SYNTAX IndexAB
            MAX-ACCESS not-accessible
            STATUS current
            DESCRIPTION
                "This index distinguishes the exiters.
                Necessary if you have dual drive transmitters."
            ::= { txInpIfNotificationEntry 2 }

        
        txInpIfNotificationInputIdx OBJECT-TYPE
            SYNTAX INTEGER
                {
                input1(1),
                input2(2)
                }
            MAX-ACCESS not-accessible
            STATUS current
            DESCRIPTION
                "Input index.
                For txInpIfState(4000) it names the logical input,
                for the others the physical input."
            ::= { txInpIfNotificationEntry 3 }

        
        txInpIfNotificationIdx OBJECT-TYPE
            SYNTAX Unsigned32 (3000..3021)
            MAX-ACCESS not-accessible
            STATUS current
            DESCRIPTION
                "The notification number as below rsXx9TxNotifications.
                This is a helper column and therefore not-accessible."
            ::= { txInpIfNotificationEntry 4 }

        
        txInpIfNotificationName OBJECT-TYPE
            SYNTAX INTEGER
                {
                txInpIfLogState(3000),
                txInpIfLogInfoPacket(3001),
                txInpIfLogPacketLength(3002),
                txInpIfIpState(3003),
                txInpIfIpInfoPacket(3004),
                txInpIfIpPacketLength(3005),
                txInpIfTsState(3006),
                txInpIfTsInfoPacket(3007),
                txInpIfTsPacketLength(3008),
                txInpIfLogDatarateBufferUnderrun(3009),
                txInpIfLogDatarateBufferOverflow(3010),
                txInpIfSatInputState(3011),
                txInpIfSatInfoPacket(3012),
                txInpIfSatPacketLength(3013),
                txInpIfSatTransponderLocked(3014),
                txInpIfSatIpOutput(3015),
                txInpIfSatReceiverState(3016),
                txInpIfSatBtsStatus(3017),
                txInpIfSatDriftStatus(3018),
                txInpIfSatLinkMarginStatus(3019),
                txInpIfSatCarrierNoiseStatus(3020),
                txInpIfSatStreamTsIdMatch(3021)
                }
            MAX-ACCESS read-only
            STATUS current
            DESCRIPTION
                "The notification number as an enumeration.
                The enumeration correlates with the notifications under rsXx9TxNotifications."
            ::= { txInpIfNotificationEntry 5 }

        
        txInpIfNotificationMask OBJECT-TYPE
            SYNTAX NotificationMask
            MAX-ACCESS read-write
            STATUS current
            DESCRIPTION
                "See textual convention for details."
            ::= { txInpIfNotificationEntry 6 }

        
        txInpIfNotificationPriority OBJECT-TYPE
            SYNTAX NotificationPriority
            MAX-ACCESS read-write
            STATUS current
            DESCRIPTION
                "See textual convention for details."
            ::= { txInpIfNotificationEntry 7 }

        
        txInpIfNotificationState OBJECT-TYPE
            SYNTAX NotificationState
            MAX-ACCESS read-only
            STATUS current
            DESCRIPTION
                "See textual convention for details."
            ::= { txInpIfNotificationEntry 8 }

        
        txInpGeneralSetupTable OBJECT-TYPE
            SYNTAX SEQUENCE OF TxInpGeneralSetupEntry
            MAX-ACCESS not-accessible
            STATUS current
            DESCRIPTION
                "General input settings."
            ::= { txInputInterfaces 2 }

        
        txInpGeneralSetupEntry OBJECT-TYPE
            SYNTAX TxInpGeneralSetupEntry
            MAX-ACCESS not-accessible
            STATUS current
            DESCRIPTION
                "An entry in the txInpGeneralSetupTable."
            INDEX { txInpIfNotificationTxIdx, txInpIfNotificationExcIdx, txInpIfNotificationInputIdx }
            ::= { txInpGeneralSetupTable 1 }

        
        TxInpGeneralSetupEntry ::=
            SEQUENCE { 
                txInpGsInputSource
                    INTEGER,
                txInpGsMultiplexName
                    SnmpAdminString
             }

        txInpGsInputSource OBJECT-TYPE
            SYNTAX INTEGER
                {
                ts1(1),
                ts2(2),
                ip1(3),
                ip2(4),
                rx(5),
                eti1(6),
                eti2(7),
                sat1(8),
                sat2(9),
                edi1(10),
                edi2(11)
                }
            MAX-ACCESS read-write
            STATUS current
            DESCRIPTION
                "Determines which physical input interface is used for
                the logical input.
                
                Only available physical input interfaces may be chosen.
                If the physical input is not available or a required option key
                is missing, the chosen phyiscal input interface may not work. 
                This is especially important for devices with a very limited 
                number of inputs (e.g. TLx Basic Variant). 
                "
            ::= { txInpGeneralSetupEntry 1 }

        
        txInpGsMultiplexName OBJECT-TYPE
            SYNTAX SnmpAdminString
            MAX-ACCESS read-write
            STATUS current
            DESCRIPTION
                "An arbitrary user defined name for the multiplex
                in input stream."
            ::= { txInpGeneralSetupEntry 2 }

        
        txInpMonitorTable OBJECT-TYPE
            SYNTAX SEQUENCE OF TxInpMonitorEntry
            MAX-ACCESS not-accessible
            STATUS current
            DESCRIPTION
                "Input monitor settings."
            ::= { txInputInterfaces 3 }

        
        txInpMonitorEntry OBJECT-TYPE
            SYNTAX TxInpMonitorEntry
            MAX-ACCESS not-accessible
            STATUS current
            DESCRIPTION
                "An entry in the txInpMonitorTable."
            INDEX { txInpIfNotificationTxIdx, txInpIfNotificationExcIdx }
            ::= { txInpMonitorTable 1 }

        
        TxInpMonitorEntry ::=
            SEQUENCE { 
                txInpMonitorOut
                    INTEGER
             }

        txInpMonitorOut OBJECT-TYPE
            SYNTAX INTEGER
                {
                undefined(1),
                off(2),
                activeInput(3),
                logicalInput1(4),
                logicalInput2(5),
                testSignal(6),
                fctZeroPulse(7)
                }
            MAX-ACCESS read-write
            STATUS current
            DESCRIPTION
                "Selects an input signal to relay to the monitor out connector (X22).
                undefined(1) must not be set.
                
                The admissible choices are determined by the installed input interface
                and option keys. testSignal(6) is not allowed for ISDB-T transmitters. "
            ::= { txInpMonitorEntry 1 }

        
        txInputIpFeedTable OBJECT-TYPE
            SYNTAX SEQUENCE OF TxInputIpFeedEntry
            MAX-ACCESS not-accessible
            STATUS current
            DESCRIPTION
                "IP feed parameters."
            ::= { txInputInterfaces 4 }

        
        txInputIpFeedEntry OBJECT-TYPE
            SYNTAX TxInputIpFeedEntry
            MAX-ACCESS not-accessible
            STATUS current
            DESCRIPTION
                "An entry in the txInputIpFeedTable."
            INDEX { txInpIfNotificationTxIdx, txInpIfNotificationExcIdx, txInpIfNotificationInputIdx }
            ::= { txInputIpFeedTable 1 }

        
        TxInputIpFeedEntry ::=
            SEQUENCE { 
                txIpFeedDatarate
                    Unsigned32,
                txIpFeedConnector
                    INTEGER,
                txIpFeedStreamingMode
                    INTEGER,
                txIpFeedStreamAddressType
                    InetAddressType,
                txIpFeedStreamAddress
                    InetAddress,
                txIpFeedStreamPort
                    Unsigned32,
                txIpFeedStreamProtocol
                    INTEGER,
                txIpFeedPacketsTotal
                    Counter64,
                txIpFeedPacketsMissing
                    Counter64,
                txIpFeedPacketsFixed
                    Counter64,
                txIpFeedPacketsDuplicate
                    Counter64,
                txIpFeedPacketsReordered
                    Counter64,
                txIpFeedPacketsOutOfRange
                    Counter64,
                txIpFeedLinkStatus
                    INTEGER
             }

        txIpFeedDatarate OBJECT-TYPE
            SYNTAX Unsigned32
            UNITS "bits per second"
            MAX-ACCESS read-only
            STATUS current
            DESCRIPTION
                "Indicates the total data rate (gross data rate) on the IP feed."
            ::= { txInputIpFeedEntry 1 }

        
        txIpFeedConnector OBJECT-TYPE
            SYNTAX INTEGER
                {
                tsLan1(1),
                tsLan2(2)
                }
            MAX-ACCESS read-write
            STATUS current
            DESCRIPTION
                "Used to define the physical network interface to which the logical IP stream 
                is bound. Normally, the TS LAN 1 socket (X30) is coupled to IP stream 1 and 
                the TS LAN 2 socket (X31) to IP stream 2. This allows you to use multiple 
                redundant servers that can be selected automatically using the automatic 
                input signal switchover. However, it is also possible to feed several 
                multicast streams via the same physical Ethernet socket. In this case, too, 
                the automatic input signal switchover function can toggle automatically 
                between two data streams.
                "
            ::= { txInputIpFeedEntry 2 }

        
        txIpFeedStreamingMode OBJECT-TYPE
            SYNTAX INTEGER
                {
                uniCast(1),
                multiCast(2)
                }
            MAX-ACCESS read-write
            STATUS current
            DESCRIPTION
                "Determines the streaming mode."
            ::= { txInputIpFeedEntry 3 }

        
        txIpFeedStreamAddressType OBJECT-TYPE
            SYNTAX InetAddressType
            MAX-ACCESS read-only
            STATUS current
            DESCRIPTION
                "Specifies the accepted internet address type for ipStreamAddress."
            ::= { txInputIpFeedEntry 4 }

        
        txIpFeedStreamAddress OBJECT-TYPE
            SYNTAX InetAddress
            MAX-ACCESS read-write
            STATUS current
            DESCRIPTION
                "If ipStreamMode is unicast(1) this object is read-only and shows the IP address
                on the physical connector.
                If ipStreamMode is multicast(2) this object is read-write for configuration
                of the multicast source the IP address.
                "
            ::= { txInputIpFeedEntry 5 }

        
        txIpFeedStreamPort OBJECT-TYPE
            SYNTAX Unsigned32 (1..65535)
            MAX-ACCESS read-write
            STATUS current
            DESCRIPTION
                "The port of the logical input stream."
            ::= { txInputIpFeedEntry 6 }

        
        txIpFeedStreamProtocol OBJECT-TYPE
            SYNTAX INTEGER
                {
                auto(1),
                udp(2),
                rtp(3)
                }
            MAX-ACCESS read-write
            STATUS current
            DESCRIPTION
                "The protocol of the logical input stream."
            ::= { txInputIpFeedEntry 7 }

        
        txIpFeedPacketsTotal OBJECT-TYPE
            SYNTAX Counter64
            MAX-ACCESS read-only
            STATUS current
            DESCRIPTION
                "Total count of all received TSoverIP packets."
            ::= { txInputIpFeedEntry 8 }

        
        txIpFeedPacketsMissing OBJECT-TYPE
            SYNTAX Counter64
            MAX-ACCESS read-only
            STATUS current
            DESCRIPTION
                "Count of all missing packets."
            ::= { txInputIpFeedEntry 9 }

        
        txIpFeedPacketsFixed OBJECT-TYPE
            SYNTAX Counter64
            MAX-ACCESS read-only
            STATUS current
            DESCRIPTION
                "Count of all packets, which were reconstructed via FEC. "
            ::= { txInputIpFeedEntry 10 }

        
        txIpFeedPacketsDuplicate OBJECT-TYPE
            SYNTAX Counter64
            MAX-ACCESS read-only
            STATUS current
            DESCRIPTION
                "Cound of packets, which were received multiple times."
            ::= { txInputIpFeedEntry 11 }

        
        txIpFeedPacketsReordered OBJECT-TYPE
            SYNTAX Counter64
            MAX-ACCESS read-only
            STATUS current
            DESCRIPTION
                "Count of packets, which had to be sorted into the correct order."
            ::= { txInputIpFeedEntry 12 }

        
        txIpFeedPacketsOutOfRange OBJECT-TYPE
            SYNTAX Counter64
            MAX-ACCESS read-only
            STATUS current
            DESCRIPTION
                "Cound of all packets, which were not in the current processing window. "
            ::= { txInputIpFeedEntry 13 }

        
        txIpFeedLinkStatus OBJECT-TYPE
            SYNTAX INTEGER
                {
                undefined(1),
                notPresent(2),
                present(3)
                }
            MAX-ACCESS read-only
            STATUS current
            DESCRIPTION
                "Description."
            ::= { txInputIpFeedEntry 14 }

        
        txInputTsFeedTable OBJECT-TYPE
            SYNTAX SEQUENCE OF TxInputTsFeedEntry
            MAX-ACCESS not-accessible
            STATUS current
            DESCRIPTION
                "TS feed parameters."
            ::= { txInputInterfaces 5 }

        
        txInputTsFeedEntry OBJECT-TYPE
            SYNTAX TxInputTsFeedEntry
            MAX-ACCESS not-accessible
            STATUS current
            DESCRIPTION
                "An entry in the txInputTsFeedTable."
            INDEX { txInpIfNotificationTxIdx, txInpIfNotificationExcIdx, txInpIfNotificationInputIdx }
            ::= { txInputTsFeedTable 1 }

        
        TxInputTsFeedEntry ::=
            SEQUENCE { 
                txTsFeedBruttoDataRate
                    Unsigned32,
                txTsFeedNettoDataRate
                    Unsigned32,
                txTsFeedPacketLength
                    Unsigned32,
                txTsFeedType
                    INTEGER
             }

        txTsFeedBruttoDataRate OBJECT-TYPE
            SYNTAX Unsigned32
            UNITS "bits per second"
            MAX-ACCESS read-only
            STATUS current
            DESCRIPTION
                "Gross data rate of the TS stream."
            ::= { txInputTsFeedEntry 1 }

        
        txTsFeedNettoDataRate OBJECT-TYPE
            SYNTAX Unsigned32
            UNITS "bits per second"
            MAX-ACCESS read-only
            STATUS current
            DESCRIPTION
                "Net data rate (without stuffing bytes) of the TS stream.
                This value is available only when txSfnTimeSyncSFN is off(2)."
            ::= { txInputTsFeedEntry 2 }

        
        txTsFeedPacketLength OBJECT-TYPE
            SYNTAX Unsigned32
            UNITS "bytes"
            MAX-ACCESS read-only
            STATUS current
            DESCRIPTION
                "Dectected packet length of TS stream."
            ::= { txInputTsFeedEntry 3 }

        
        txTsFeedType OBJECT-TYPE
            SYNTAX INTEGER
                {
                auto(1),
                asi(2),
                smpte(3)
                }
            MAX-ACCESS read-write
            STATUS current
            DESCRIPTION
                "Used to set the data format for the data streams at X20 and X21.
                auto(1)  - Data format is detected automatically
                asi(2)   - Manual setting for an ASI transport stream
                smpte(3) - Manual setting for an SMPTE transport stream"
            ::= { txInputTsFeedEntry 4 }

        
        txInputSatFeed OBJECT IDENTIFIER ::= { txInputInterfaces 6 }

        
        txInputSatFeedTunerTable OBJECT-TYPE
            SYNTAX SEQUENCE OF TxInputSatFeedTunerEntry
            MAX-ACCESS not-accessible
            STATUS current
            DESCRIPTION
                "SAT tuner parameters."
            ::= { txInputSatFeed 1 }

        
        txInputSatFeedTunerEntry OBJECT-TYPE
            SYNTAX TxInputSatFeedTunerEntry
            MAX-ACCESS not-accessible
            STATUS current
            DESCRIPTION
                "An entry in the txInputSatFeedTunerTable"
            INDEX { txInpIfNotificationTxIdx, txInpIfNotificationExcIdx, txInpIfNotificationInputIdx }
            ::= { txInputSatFeedTunerTable 1 }

        
        TxInputSatFeedTunerEntry ::=
            SEQUENCE { 
                txSatTunerTransponderFreq
                    Counter64,
                txSatTunerSignalType
                    SatSignalType,
                txSatTunerSymbolRate
                    Unsigned32,
                txSatTunerModulation
                    INTEGER,
                txSatTunerCoderate
                    SnmpAdminString,
                txSatTunerSignalStandard
                    SatSignalType,
                txSatTunerRxPower
                    Integer32,
                txSatTunerMeasuredTsDatarate
                    Unsigned32,
                txSatTunerBitErrorRate
                    Unsigned32,
                txSatTunerCarrierNoiseRatio
                    Integer32,
                txSatTunerTsSymbolRate
                    Unsigned32,
                txSatTunerIntermediateFreq
                    Counter64,
                txSatTunerLinkMargin
                    Integer32,
                txSatTunerLinkMarginWarnLimit
                    Integer32,
                txSatTunerLinkMarginFaultLimit
                    Integer32,
                txSatTunerCarrierNoiseWarnLimit
                    Integer32,
                txSatTunerCarrierNoiseFaultLimit
                    Integer32,
                txSatTunerTransponderFreqUpper32
                    Unsigned32,
                txSatTunerTransponderFreqLower32
                    Unsigned32
             }

        txSatTunerTransponderFreq OBJECT-TYPE
            SYNTAX Counter64
            UNITS "Hz"
            MAX-ACCESS read-only
            STATUS current
            DESCRIPTION
                "Description.
                
                range: 950000000 - 12750000000 [Hz] (equals 950 MHz - 12.75 GHz)"
            ::= { txInputSatFeedTunerEntry 1 }

        
        txSatTunerSignalType OBJECT-TYPE
            SYNTAX SatSignalType
            MAX-ACCESS read-write
            STATUS current
            DESCRIPTION
                "Expected signal type that shall be received."
            ::= { txInputSatFeedTunerEntry 2 }

        
        txSatTunerSymbolRate OBJECT-TYPE
            SYNTAX Unsigned32 (0..50000000)
            UNITS "Sps"
            MAX-ACCESS read-write
            STATUS current
            DESCRIPTION
                "Expected symbol rate of the signal that shall 
                be received in kSymb/s. If 0 is entered here,
                 the DVB-S/S2 receiver will perform a Blind 
                Search and try to detected all signal parameters
                automatically."
            ::= { txInputSatFeedTunerEntry 3 }

        
        txSatTunerModulation OBJECT-TYPE
            SYNTAX INTEGER
                {
                undefinedMode(1),
                qpsk(2),
                psk8(3),
                psk16(4),
                psk32(5)
                }
            MAX-ACCESS read-only
            STATUS current
            DESCRIPTION
                "The detected modulation of the received signal"
            ::= { txInputSatFeedTunerEntry 4 }

        
        txSatTunerCoderate OBJECT-TYPE
            SYNTAX SnmpAdminString (SIZE (0..16))
            MAX-ACCESS read-only
            STATUS current
            DESCRIPTION
                "The current FEC code rate of the received signal"
            ::= { txInputSatFeedTunerEntry 5 }

        
        txSatTunerSignalStandard OBJECT-TYPE
            SYNTAX SatSignalType
            MAX-ACCESS read-only
            STATUS current
            DESCRIPTION
                "The detected signal standard of the received signal"
            ::= { txInputSatFeedTunerEntry 6 }

        
        txSatTunerRxPower OBJECT-TYPE
            SYNTAX Integer32 (-9000..0)
            UNITS "0.01dBm"
            MAX-ACCESS read-only
            STATUS current
            DESCRIPTION
                "The current received power in 0.01 dBm"
            ::= { txInputSatFeedTunerEntry 7 }

        
        txSatTunerMeasuredTsDatarate OBJECT-TYPE
            SYNTAX Unsigned32
            UNITS "bps"
            MAX-ACCESS read-only
            STATUS current
            DESCRIPTION
                "The measured data rate of the transport stream in Bit/s"
            ::= { txInputSatFeedTunerEntry 8 }

        
        txSatTunerBitErrorRate OBJECT-TYPE
            SYNTAX Unsigned32
            MAX-ACCESS read-only
            STATUS current
            DESCRIPTION
                "The current bit error rate."
            ::= { txInputSatFeedTunerEntry 9 }

        
        txSatTunerCarrierNoiseRatio OBJECT-TYPE
            SYNTAX Integer32 (-300..20000)
            UNITS "0.01dB"
            MAX-ACCESS read-only
            STATUS current
            DESCRIPTION
                "The current carrier-to-noise ratio in 0.01 dB."
            ::= { txInputSatFeedTunerEntry 10 }

        
        txSatTunerTsSymbolRate OBJECT-TYPE
            SYNTAX Unsigned32 (0..50000000)
            UNITS "Sps"
            MAX-ACCESS read-only
            STATUS current
            DESCRIPTION
                "The current symbol rate of the received signal 
                in Symb/s (including the SR offset)"
            ::= { txInputSatFeedTunerEntry 11 }

        
        txSatTunerIntermediateFreq OBJECT-TYPE
            SYNTAX Counter64
            UNITS "Hz"
            MAX-ACCESS read-only
            STATUS current
            DESCRIPTION
                "The intermediate frequency is calculated from the LNB
                Frequency and the selected Transponder Frequency."
            ::= { txInputSatFeedTunerEntry 12 }

        
        txSatTunerLinkMargin OBJECT-TYPE
            SYNTAX Integer32
            UNITS "0.1 dB"
            MAX-ACCESS read-only
            STATUS current
            DESCRIPTION
                "The difference between the receiver's sensitivity 
                (i.e., the received power at which the receiver will 
                stop working) and the actual received power."
            ::= { txInputSatFeedTunerEntry 13 }

        
        txSatTunerLinkMarginWarnLimit OBJECT-TYPE
            SYNTAX Integer32 (0..2000)
            UNITS "0.01dB"
            MAX-ACCESS read-write
            STATUS current
            DESCRIPTION
                "Indicates the threshold for a link margin warning. "
            ::= { txInputSatFeedTunerEntry 14 }

        
        txSatTunerLinkMarginFaultLimit OBJECT-TYPE
            SYNTAX Integer32 (0..2000)
            UNITS "0.01dB"
            MAX-ACCESS read-write
            STATUS current
            DESCRIPTION
                "Indicates the threshold for a link margin fault."
            ::= { txInputSatFeedTunerEntry 15 }

        
        txSatTunerCarrierNoiseWarnLimit OBJECT-TYPE
            SYNTAX Integer32 (0..2000)
            UNITS "0.01dB"
            MAX-ACCESS read-write
            STATUS current
            DESCRIPTION
                "When the C/N drops below this limit a warning is indicated.
                "
            ::= { txInputSatFeedTunerEntry 16 }

        
        txSatTunerCarrierNoiseFaultLimit OBJECT-TYPE
            SYNTAX Integer32 (0..2000)
            UNITS "0.01dB"
            MAX-ACCESS read-write
            STATUS current
            DESCRIPTION
                "When the C/N drops below this limit a fault is indicated.
                "
            ::= { txInputSatFeedTunerEntry 17 }

        
        txSatTunerTransponderFreqUpper32 OBJECT-TYPE
            SYNTAX Unsigned32
            MAX-ACCESS read-write
            STATUS current
            DESCRIPTION
                "Description.
                these are the upper 32bits of a 64bit value
                
                range: 950000000 - 12750000000 [Hz] (equals 950 MHz - 12.75 GHz)"
            ::= { txInputSatFeedTunerEntry 18 }

        
        txSatTunerTransponderFreqLower32 OBJECT-TYPE
            SYNTAX Unsigned32
            MAX-ACCESS read-write
            STATUS current
            DESCRIPTION
                "Description.
                these are the lower 32bits of a 64bit value
                
                range: 950000000 - 12750000000 [Hz] (equals 950 MHz - 12.75 GHz)"
            ::= { txInputSatFeedTunerEntry 19 }

        
        txInputSatFeedLnbTable OBJECT-TYPE
            SYNTAX SEQUENCE OF TxInputSatFeedLnbEntry
            MAX-ACCESS not-accessible
            STATUS current
            DESCRIPTION
                "SAT LNB parameters."
            ::= { txInputSatFeed 2 }

        
        txInputSatFeedLnbEntry OBJECT-TYPE
            SYNTAX TxInputSatFeedLnbEntry
            MAX-ACCESS not-accessible
            STATUS current
            DESCRIPTION
                "An entry in the txInputSatFeedLnbTable"
            INDEX { txInpIfNotificationTxIdx, txInpIfNotificationExcIdx, txInpIfNotificationInputIdx }
            ::= { txInputSatFeedLnbTable 1 }

        
        TxInputSatFeedLnbEntry ::=
            SEQUENCE { 
                txSatLnbPolarization
                    INTEGER,
                txSatLnbFreqLowBand
                    Counter64,
                txSatLnbFreqHighBand
                    Counter64,
                txSatLnbVoltage
                    INTEGER,
                txSatLnbBand
                    INTEGER,
                txSatLnbFreqCBand
                    Counter64,
                txSatLnb22kHzSignal
                    SwitchOnOff,
                txSatLnbDriftWarnLimit
                    Unsigned32,
                txSatLnbDrift
                    Integer32,
                txSatLnbFreqLowBandUpper32
                    Unsigned32,
                txSatLnbFreqLowBandLower32
                    Unsigned32,
                txSatLnbFreqHighBandUpper32
                    Unsigned32,
                txSatLnbFreqHighBandLower32
                    Unsigned32,
                txSatLnbFreqCBandUpper32
                    Unsigned32,
                txSatLnbFreqCBandLower32
                    Unsigned32
             }

        txSatLnbPolarization OBJECT-TYPE
            SYNTAX INTEGER
                {
                horizontal(1),
                vertical(2)
                }
            MAX-ACCESS read-write
            STATUS current
            DESCRIPTION
                "The polarisation that shall be selected by the LNB. 
                If horizontal polarisation is selected, the LNB 
                supply voltage will be increased from 13V/14V to 
                18V/19V. This parameter has no effect if the LNB 
                Voltage is set to Off."
            ::= { txInputSatFeedLnbEntry 1 }

        
        txSatLnbFreqLowBand OBJECT-TYPE
            SYNTAX Counter64
            UNITS "Hz"
            MAX-ACCESS read-only
            STATUS current
            DESCRIPTION
                "Frequency of the local oscillator of the LNB in the 
                low band in MHz (Ku-Band only). The software 
                calculates if the selected transponder frequency 
                falls into the low or high band of the LNB.
                
                range: 9300000000 - 10200000000 [Hz] (equals 9.3GHz - 10.2 GHz)
                "
            ::= { txInputSatFeedLnbEntry 2 }

        
        txSatLnbFreqHighBand OBJECT-TYPE
            SYNTAX Counter64
            UNITS "Hz"
            MAX-ACCESS read-only
            STATUS current
            DESCRIPTION
                "Frequency of the local oscillator of the LNB in the 
                high band in MHz (Ku-Band only).
                The software calculates if the selected transponder 
                frequency falls into the low or high band of the LNB.
                If the high band shall be used a 22kHz tone will be 
                automatically transmitted to the LNB.
                
                range: 10200000000 - 11000000000 [Hz] (equals 10.2GHz - 11.00 GHz)
                "
            ::= { txInputSatFeedLnbEntry 3 }

        
        txSatLnbVoltage OBJECT-TYPE
            SYNTAX INTEGER
                {
                off(1),
                vert13VandHori18V(2),
                vert14VandHori19V(3)
                }
            MAX-ACCESS read-write
            STATUS current
            DESCRIPTION
                "Selects the LNB supply voltage. The voltage supplied 
                to the LNB can be increased by about 1V to cope with
                losses due to the resistance of the RF cable."
            ::= { txInputSatFeedLnbEntry 4 }

        
        txSatLnbBand OBJECT-TYPE
            SYNTAX INTEGER
                {
                kuBand(1),
                cBand(2),
                manual(3)
                }
            MAX-ACCESS read-write
            STATUS current
            DESCRIPTION
                "This parameter determines how the selected IF 
                of the DVB-S/S2 Tuner is calculated.
                - In C-Band Mode only one LNB frequency is 
                used and the 22kHz tonecan be switched on or 
                off manually.
                - In Ku-Band Mode two LNB frequencies (high 
                and low) have to be entered. The device 
                automatically selects the matching frequency 
                band and switches the 22kHz tone on if the 
                high band should be selected.
                - In Manual Mode you can directly enter the 
                intermediate frequency (IF) which the Tuner
                shall attempt to receive.
                "
            ::= { txInputSatFeedLnbEntry 5 }

        
        txSatLnbFreqCBand OBJECT-TYPE
            SYNTAX Counter64
            UNITS "Hz"
            MAX-ACCESS read-only
            STATUS current
            DESCRIPTION
                "Frequency of the local oscillator of the LNB in Hz (C-Band only).
                
                range: 3 000 000 000 - 6 000 000 000 [Hz] (equals 3GHz - 6.00 GHz)"
            ::= { txInputSatFeedLnbEntry 6 }

        
        txSatLnb22kHzSignal OBJECT-TYPE
            SYNTAX SwitchOnOff
            MAX-ACCESS read-write
            STATUS current
            DESCRIPTION
                "Manually controls the 22kHz tone transmitted to the 
                LNB (only relevant in LNB Modes C-Band and Manual)."
            ::= { txInputSatFeedLnbEntry 7 }

        
        txSatLnbDriftWarnLimit OBJECT-TYPE
            SYNTAX Unsigned32 (0..1000000)
            UNITS "Hz"
            MAX-ACCESS read-write
            STATUS current
            DESCRIPTION
                "When the difference between receive frequency and transponder 
                frequency rises above this limit a warning is indicated.
                "
            ::= { txInputSatFeedLnbEntry 8 }

        
        txSatLnbDrift OBJECT-TYPE
            SYNTAX Integer32
            UNITS "kHz"
            MAX-ACCESS read-only
            STATUS current
            DESCRIPTION
                "Indicates a warning when the difference between transponder frequency 
                and receive frequency (tuner frequency) is too high. "
            ::= { txInputSatFeedLnbEntry 9 }

        
        txSatLnbFreqLowBandUpper32 OBJECT-TYPE
            SYNTAX Unsigned32
            MAX-ACCESS read-write
            STATUS current
            DESCRIPTION
                "Frequency of the local oscillator of the LNB in the 
                low band in MHz (Ku-Band only). The software 
                calculates if the selected transponder frequency 
                falls into the low or high band of the LNB.
                these are the upper 32bits of a 64bit value
                
                range: 9300000000 - 10200000000 [Hz] (equals 9.3GHz - 10.2 GHz)
                "
            ::= { txInputSatFeedLnbEntry 10 }

        
        txSatLnbFreqLowBandLower32 OBJECT-TYPE
            SYNTAX Unsigned32
            MAX-ACCESS read-write
            STATUS current
            DESCRIPTION
                "Frequency of the local oscillator of the LNB in the 
                low band in MHz (Ku-Band only). The software 
                calculates if the selected transponder frequency 
                falls into the low or high band of the LNB.
                these are the lower 32bits of a 64bit value
                
                range: 9300000000 - 10200000000 [Hz] (equals 9.3GHz - 10.2 GHz)
                "
            ::= { txInputSatFeedLnbEntry 11 }

        
        txSatLnbFreqHighBandUpper32 OBJECT-TYPE
            SYNTAX Unsigned32
            MAX-ACCESS read-write
            STATUS current
            DESCRIPTION
                "Frequency of the local oscillator of the LNB in the 
                high band in MHz (Ku-Band only).
                The software calculates if the selected transponder 
                frequency falls into the low or high band of the LNB.
                If the high band shall be used a 22kHz tone will be 
                automatically transmitted to the LNB.
                these are the upper 32bits of a 64bit value
                
                range: 10200000000 - 11000000000 [Hz] (equals 10.2GHz - 11.00 GHz)
                "
            ::= { txInputSatFeedLnbEntry 12 }

        
        txSatLnbFreqHighBandLower32 OBJECT-TYPE
            SYNTAX Unsigned32
            MAX-ACCESS read-write
            STATUS current
            DESCRIPTION
                "Frequency of the local oscillator of the LNB in the 
                high band in MHz (Ku-Band only).
                The software calculates if the selected transponder 
                frequency falls into the low or high band of the LNB.
                If the high band shall be used a 22kHz tone will be 
                automatically transmitted to the LNB.
                these are the lower 32bits of a 64bit value
                
                range: 10200000000 - 11000000000 [Hz] (equals 10.2GHz - 11.00 GHz)
                "
            ::= { txInputSatFeedLnbEntry 13 }

        
        txSatLnbFreqCBandUpper32 OBJECT-TYPE
            SYNTAX Unsigned32
            MAX-ACCESS read-write
            STATUS current
            DESCRIPTION
                "Frequency of the local oscillator of the LNB in Hz (C-Band only).
                these are the upper 32bits of a 64bit value
                
                range: 3 000 000 000 - 6 000 000 000 [Hz] (equals 3GHz - 6.00 GHz)"
            ::= { txInputSatFeedLnbEntry 14 }

        
        txSatLnbFreqCBandLower32 OBJECT-TYPE
            SYNTAX Unsigned32
            MAX-ACCESS read-write
            STATUS current
            DESCRIPTION
                "Frequency of the local oscillator of the LNB in Hz (C-Band only).
                these are the lower 32bits of a 64bit value
                
                range: 3 000 000 000 - 6 000 000 000 [Hz] (equals 3GHz - 6.00 GHz)"
            ::= { txInputSatFeedLnbEntry 15 }

        
        txInputSatFeedCamTable OBJECT-TYPE
            SYNTAX SEQUENCE OF TxInputSatFeedCamEntry
            MAX-ACCESS not-accessible
            STATUS current
            DESCRIPTION
                "SAT CAM parameters."
            ::= { txInputSatFeed 3 }

        
        txInputSatFeedCamEntry OBJECT-TYPE
            SYNTAX TxInputSatFeedCamEntry
            MAX-ACCESS not-accessible
            STATUS current
            DESCRIPTION
                "An entry in the txInputSatFeedCamTable"
            INDEX { txInpIfNotificationTxIdx, txInpIfNotificationExcIdx, txInpIfNotificationInputIdx }
            ::= { txInputSatFeedCamTable 1 }

        
        TxInputSatFeedCamEntry ::=
            SEQUENCE { 
                txSatCamInserted
                    TruthValue,
                txSatCamStatus
                    INTEGER,
                txSatCamManufacturerName
                    SnmpAdminString,
                txSatCamModuleName
                    SnmpAdminString,
                txSatCamTsInput
                    TruthValue,
                txSatCamTsOutput
                    TruthValue,
                txSatCamConfigurationMode
                    INTEGER,
                txSatCamBissMode
                    INTEGER,
                txSatCamBissInjectedId
                    SnmpAdminString,
                txSatCamBissEncryptedSession
                    SnmpAdminString,
                txSatCamBissClearSession
                    SnmpAdminString,
                txSatCamScInserted
                    TruthValue,
                txSatCamScManufacturerName
                    SnmpAdminString,
                txSatCamScExpirationDate
                    DateAndTime,
                txSatCamResetMode
                    INTEGER,
                txSatCamReset
                    Trigger
             }

        txSatCamInserted OBJECT-TYPE
            SYNTAX TruthValue
            MAX-ACCESS read-only
            STATUS current
            DESCRIPTION
                "Indicates whether a CAM is installed. CAM=Conditional Access Module
                "
            ::= { txInputSatFeedCamEntry 1 }

        
        txSatCamStatus OBJECT-TYPE
            SYNTAX INTEGER
                {
                off(1),
                on(2),
                noModule(3),
                noSignal(4),
                noKey(5),
                needMMI(6)
                }
            MAX-ACCESS read-only
            STATUS current
            DESCRIPTION
                "Status of the Condtional Access Module. "
            ::= { txInputSatFeedCamEntry 2 }

        
        txSatCamManufacturerName OBJECT-TYPE
            SYNTAX SnmpAdminString (SIZE (0..64))
            MAX-ACCESS read-only
            STATUS current
            DESCRIPTION
                "The manufacturer of the CA module."
            ::= { txInputSatFeedCamEntry 3 }

        
        txSatCamModuleName OBJECT-TYPE
            SYNTAX SnmpAdminString (SIZE (0..64))
            MAX-ACCESS read-only
            STATUS current
            DESCRIPTION
                "The name of the CA module."
            ::= { txInputSatFeedCamEntry 4 }

        
        txSatCamTsInput OBJECT-TYPE
            SYNTAX TruthValue
            MAX-ACCESS read-only
            STATUS current
            DESCRIPTION
                "Description."
            ::= { txInputSatFeedCamEntry 5 }

        
        txSatCamTsOutput OBJECT-TYPE
            SYNTAX TruthValue
            MAX-ACCESS read-only
            STATUS current
            DESCRIPTION
                "Indicates whether a transport stream has been detected at the 
                output of the conditional access module."
            ::= { txInputSatFeedCamEntry 6 }

        
        txSatCamConfigurationMode OBJECT-TYPE
            SYNTAX INTEGER
                {
                undefinedCam(1),
                off(2),
                ci(3),
                biss(4)
                }
            MAX-ACCESS read-write
            STATUS current
            DESCRIPTION
                "Selects the operation mode of CAM 1/2. You can use 
                the internal BISS-E core or an additional CA Module 
                in Common Interface Slot 1/2 for descrambling a
                Transport Stream.
                "
            ::= { txInputSatFeedCamEntry 7 }

        
        txSatCamBissMode OBJECT-TYPE
            SYNTAX INTEGER
                {
                undefinedMode(1),
                bissE(2),
                biss1(3)
                }
            MAX-ACCESS read-write
            STATUS current
            DESCRIPTION
                "Operation Mode of the BISS core."
            ::= { txInputSatFeedCamEntry 8 }

        
        txSatCamBissInjectedId OBJECT-TYPE
            SYNTAX SnmpAdminString (SIZE (0..64))
            MAX-ACCESS read-write
            STATUS current
            DESCRIPTION
                "Enter the default 14 character Injected Identifier used 
                for BISS-E here."
            ::= { txInputSatFeedCamEntry 9 }

        
        txSatCamBissEncryptedSession OBJECT-TYPE
            SYNTAX SnmpAdminString (SIZE (0..64))
            MAX-ACCESS read-write
            STATUS current
            DESCRIPTION
                "Enter the default 16 character Encrypted Session 
                Word used for BISS-E here."
            ::= { txInputSatFeedCamEntry 10 }

        
        txSatCamBissClearSession OBJECT-TYPE
            SYNTAX SnmpAdminString (SIZE (0..64))
            MAX-ACCESS read-write
            STATUS current
            DESCRIPTION
                "Enter the default 12 character Clear Session Word 
                used for BISS-1 here."
            ::= { txInputSatFeedCamEntry 11 }

        
        txSatCamScInserted OBJECT-TYPE
            SYNTAX TruthValue
            MAX-ACCESS read-only
            STATUS current
            DESCRIPTION
                "Indicates whether a Smartcard is installed."
            ::= { txInputSatFeedCamEntry 12 }

        
        txSatCamScManufacturerName OBJECT-TYPE
            SYNTAX SnmpAdminString (SIZE (0..64))
            MAX-ACCESS read-only
            STATUS current
            DESCRIPTION
                "Shows the manufacturer name of the Smartcard."
            ::= { txInputSatFeedCamEntry 13 }

        
        txSatCamScExpirationDate OBJECT-TYPE
            SYNTAX DateAndTime
            MAX-ACCESS read-only
            STATUS current
            DESCRIPTION
                "Indicates the expiraton date of Smartcard."
            ::= { txInputSatFeedCamEntry 14 }

        
        txSatCamResetMode OBJECT-TYPE
            SYNTAX INTEGER
                {
                manual(1),
                auto(2)
                }
            MAX-ACCESS read-write
            STATUS current
            DESCRIPTION
                "Indicates whether the conditional access module is reset automatically 
                in case of  malfunction. "
            ::= { txInputSatFeedCamEntry 15 }

        
        txSatCamReset OBJECT-TYPE
            SYNTAX Trigger
            MAX-ACCESS read-write
            STATUS current
            DESCRIPTION
                "Resets the conditional access module manually.
                "
            ::= { txInputSatFeedCamEntry 16 }

        
        txInputSatFeedIpOutputTable OBJECT-TYPE
            SYNTAX SEQUENCE OF TxInputSatFeedIpOutputEntry
            MAX-ACCESS not-accessible
            STATUS current
            DESCRIPTION
                "SAT IP output parameters."
            ::= { txInputSatFeed 4 }

        
        txInputSatFeedIpOutputEntry OBJECT-TYPE
            SYNTAX TxInputSatFeedIpOutputEntry
            MAX-ACCESS not-accessible
            STATUS current
            DESCRIPTION
                "An entry in the txInputSatFeedIpOutputTable"
            INDEX { txInpIfNotificationTxIdx, txInpIfNotificationExcIdx, txInpIfNotificationInputIdx }
            ::= { txInputSatFeedIpOutputTable 1 }

        
        TxInputSatFeedIpOutputEntry ::=
            SEQUENCE { 
                txSatIpOutMulticastAddrType
                    InetAddressType,
                txSatIpOutPort
                    Unsigned32,
                txSatIpOutMulticastAddr
                    InetAddress,
                txSatIpOutFecRow
                    Unsigned32,
                txSatIpOutFecCol
                    Unsigned32,
                txSatIpOutLocalIpAddrType
                    InetAddressType,
                txSatIpOutLocalIpAddr
                    InetAddress,
                txSatIpOutLocalNetmaskAddrType
                    InetAddressType,
                txSatIpOutLocalNetmask
                    InetAddress,
                txSatIpOutMacAddr
                    SnmpAdminString
             }

        txSatIpOutMulticastAddrType OBJECT-TYPE
            SYNTAX InetAddressType
            MAX-ACCESS read-only
            STATUS current
            DESCRIPTION
                "Specifies the accepted internet address type for txSatIpOutMulticastAddr."
            ::= { txInputSatFeedIpOutputEntry 1 }

        
        txSatIpOutPort OBJECT-TYPE
            SYNTAX Unsigned32 (0..65535)
            MAX-ACCESS read-write
            STATUS current
            DESCRIPTION
                "Description."
            ::= { txInputSatFeedIpOutputEntry 2 }

        
        txSatIpOutMulticastAddr OBJECT-TYPE
            SYNTAX InetAddress
            MAX-ACCESS read-write
            STATUS current
            DESCRIPTION
                "Description."
            ::= { txInputSatFeedIpOutputEntry 3 }

        
        txSatIpOutFecRow OBJECT-TYPE
            SYNTAX Unsigned32 (4..10)
            MAX-ACCESS read-write
            STATUS current
            DESCRIPTION
                "Description."
            ::= { txInputSatFeedIpOutputEntry 4 }

        
        txSatIpOutFecCol OBJECT-TYPE
            SYNTAX Unsigned32 (4..10)
            MAX-ACCESS read-write
            STATUS current
            DESCRIPTION
                "Description."
            ::= { txInputSatFeedIpOutputEntry 5 }

        
        txSatIpOutLocalIpAddrType OBJECT-TYPE
            SYNTAX InetAddressType
            MAX-ACCESS read-only
            STATUS current
            DESCRIPTION
                "Specifies the accepted internet address type for txSatIpOutLocalIpAddrType."
            ::= { txInputSatFeedIpOutputEntry 6 }

        
        txSatIpOutLocalIpAddr OBJECT-TYPE
            SYNTAX InetAddress
            MAX-ACCESS read-write
            STATUS current
            DESCRIPTION
                "Description."
            ::= { txInputSatFeedIpOutputEntry 7 }

        
        txSatIpOutLocalNetmaskAddrType OBJECT-TYPE
            SYNTAX InetAddressType
            MAX-ACCESS read-only
            STATUS current
            DESCRIPTION
                "Specifies the accepted internet address type for txSatIpOutLocalNetmask."
            ::= { txInputSatFeedIpOutputEntry 8 }

        
        txSatIpOutLocalNetmask OBJECT-TYPE
            SYNTAX InetAddress
            MAX-ACCESS read-write
            STATUS current
            DESCRIPTION
                "Description."
            ::= { txInputSatFeedIpOutputEntry 9 }

        
        txSatIpOutMacAddr OBJECT-TYPE
            SYNTAX SnmpAdminString (SIZE (0..17))
            MAX-ACCESS read-only
            STATUS current
            DESCRIPTION
                "Description."
            ::= { txInputSatFeedIpOutputEntry 10 }

        
        txInputSatFeedInputServiceTable OBJECT-TYPE
            SYNTAX SEQUENCE OF TxInputSatFeedInputServiceEntry
            MAX-ACCESS not-accessible
            STATUS current
            DESCRIPTION
                "SAT input service parameters."
            ::= { txInputSatFeed 5 }

        
        txInputSatFeedInputServiceEntry OBJECT-TYPE
            SYNTAX TxInputSatFeedInputServiceEntry
            MAX-ACCESS not-accessible
            STATUS current
            DESCRIPTION
                "An entry in the txInputSatFeedInputServiceTable"
            INDEX { txInpIfNotificationTxIdx, txInpIfNotificationExcIdx, txInpIfNotificationInputIdx, txSatFeedServiceIdx }
            ::= { txInputSatFeedInputServiceTable 1 }

        
        TxInputSatFeedInputServiceEntry ::=
            SEQUENCE { 
                txSatFeedServiceIdx
                    Integer32,
                txSatFeedInputServiceName
                    SnmpAdminString,
                txSatFeedInputServiceID
                    Unsigned32,
                txSatFeedInputServiceType
                    SnmpAdminString,
                txSatFeedInputServiceElementaryStreams
                    Unsigned32,
                txSatFeedInputServiceDecryption
                    SwitchOnOff,
                txSatFeedInputServiceEncrypted
                    TruthValue,
                txSatFeedInputServiceDecryptionState
                    INTEGER,
                txSatFeedInputServiceDecryptedAt
                    SnmpAdminString,
                txSatFeedInputServicePmtPid
                    Unsigned32
             }

        txSatFeedServiceIdx OBJECT-TYPE
            SYNTAX Integer32 (1..32)
            MAX-ACCESS not-accessible
            STATUS current
            DESCRIPTION
                "The input service index. 
                "
            ::= { txInputSatFeedInputServiceEntry 1 }

        
        txSatFeedInputServiceName OBJECT-TYPE
            SYNTAX SnmpAdminString (SIZE (0..64))
            MAX-ACCESS read-only
            STATUS current
            DESCRIPTION
                "The name of the service (from SDT)"
            ::= { txInputSatFeedInputServiceEntry 2 }

        
        txSatFeedInputServiceID OBJECT-TYPE
            SYNTAX Unsigned32 (0..65535)
            MAX-ACCESS read-only
            STATUS current
            DESCRIPTION
                "The Service ID (from PAT)"
            ::= { txInputSatFeedInputServiceEntry 3 }

        
        txSatFeedInputServiceType OBJECT-TYPE
            SYNTAX SnmpAdminString (SIZE (0..16))
            MAX-ACCESS read-only
            STATUS current
            DESCRIPTION
                "The service type as decimal value (from SDT)"
            ::= { txInputSatFeedInputServiceEntry 4 }

        
        txSatFeedInputServiceElementaryStreams OBJECT-TYPE
            SYNTAX Unsigned32
            MAX-ACCESS read-only
            STATUS current
            DESCRIPTION
                "The number of elementary streams (ES) in this 
                service (from PMT)"
            ::= { txInputSatFeedInputServiceEntry 5 }

        
        txSatFeedInputServiceDecryption OBJECT-TYPE
            SYNTAX SwitchOnOff
            MAX-ACCESS read-write
            STATUS current
            DESCRIPTION
                "The decryption is enabled"
            ::= { txInputSatFeedInputServiceEntry 6 }

        
        txSatFeedInputServiceEncrypted OBJECT-TYPE
            SYNTAX TruthValue
            MAX-ACCESS read-only
            STATUS current
            DESCRIPTION
                "is true(1) if the service is encrypted (from SDT)"
            ::= { txInputSatFeedInputServiceEntry 7 }

        
        txSatFeedInputServiceDecryptionState OBJECT-TYPE
            SYNTAX INTEGER
                {
                undefinedStatus(1),
                no(2),
                error(3),
                ok(5)
                }
            MAX-ACCESS read-only
            STATUS current
            DESCRIPTION
                "The status of the decryption process
                "
            ::= { txInputSatFeedInputServiceEntry 8 }

        
        txSatFeedInputServiceDecryptedAt OBJECT-TYPE
            SYNTAX SnmpAdminString
            MAX-ACCESS read-only
            STATUS obsolete
            DESCRIPTION
                "obsolete"
            ::= { txInputSatFeedInputServiceEntry 9 }

        
        txSatFeedInputServicePmtPid OBJECT-TYPE
            SYNTAX Unsigned32 (0..65536)
            MAX-ACCESS read-only
            STATUS current
            DESCRIPTION
                "Indicates the ID of the service from the program map table (PMT). "
            ::= { txInputSatFeedInputServiceEntry 10 }

        
        txInputSatFeedGeneralTable OBJECT-TYPE
            SYNTAX SEQUENCE OF TxInputSatFeedGeneralEntry
            MAX-ACCESS not-accessible
            STATUS current
            DESCRIPTION
                "Description."
            ::= { txInputSatFeed 6 }

        
        txInputSatFeedGeneralEntry OBJECT-TYPE
            SYNTAX TxInputSatFeedGeneralEntry
            MAX-ACCESS not-accessible
            STATUS current
            DESCRIPTION
                "Description."
            INDEX { txInpIfNotificationTxIdx, txInpIfNotificationExcIdx }
            ::= { txInputSatFeedGeneralTable 1 }

        
        TxInputSatFeedGeneralEntry ::=
            SEQUENCE { 
                txSatGeneralAsiOutput
                    INTEGER
             }

        txSatGeneralAsiOutput OBJECT-TYPE
            SYNTAX INTEGER
                {
                off(1),
                sat1(2),
                sat2(3)
                }
            MAX-ACCESS read-write
            STATUS current
            DESCRIPTION
                "Indicates which of the two SAT receiver streams is switched to the ASI 
                output (X25) of SAT receiver board. The setting can be changed here. 
                This parameter is available if at least one logical input is configured as 
                SAT-input.
                "
            ::= { txInputSatFeedGeneralEntry 1 }

        
        txInputSatFeedDecryptionServiceTable OBJECT-TYPE
            SYNTAX SEQUENCE OF TxInputSatFeedDecryptionServiceEntry
            MAX-ACCESS not-accessible
            STATUS current
            DESCRIPTION
                "SAT input service decryption parameters."
            ::= { txInputSatFeed 7 }

        
        txInputSatFeedDecryptionServiceEntry OBJECT-TYPE
            SYNTAX TxInputSatFeedDecryptionServiceEntry
            MAX-ACCESS not-accessible
            STATUS current
            DESCRIPTION
                "An entry in the txInputSatFeedDecryptionServiceTable."
            INDEX { txInpIfNotificationTxIdx, txInpIfNotificationExcIdx, txInpIfNotificationInputIdx, txSatFeedDecryptionServiceIdx }
            ::= { txInputSatFeedDecryptionServiceTable 1 }

        
        TxInputSatFeedDecryptionServiceEntry ::=
            SEQUENCE { 
                txSatFeedDecryptionServiceIdx
                    Integer32,
                txSatFeedDecryptionServiceID
                    Unsigned32
             }

        txSatFeedDecryptionServiceIdx OBJECT-TYPE
            SYNTAX Integer32 (1..16)
            MAX-ACCESS not-accessible
            STATUS current
            DESCRIPTION
                "The input service decryption index. 
                "
            ::= { txInputSatFeedDecryptionServiceEntry 1 }

        
        txSatFeedDecryptionServiceID OBJECT-TYPE
            SYNTAX Unsigned32 (0..65535)
            MAX-ACCESS read-write
            STATUS current
            DESCRIPTION
                "Enable the decryption for this services"
            ::= { txInputSatFeedDecryptionServiceEntry 2 }

        
        txInputSatFeedBtsTable OBJECT-TYPE
            SYNTAX SEQUENCE OF TxInputSatFeedBtsEntry
            MAX-ACCESS not-accessible
            STATUS current
            DESCRIPTION
                "Description."
            ::= { txInputSatFeed 8 }

        
        txInputSatFeedBtsEntry OBJECT-TYPE
            SYNTAX TxInputSatFeedBtsEntry
            MAX-ACCESS not-accessible
            STATUS current
            DESCRIPTION
                "Description."
            INDEX { txInpIfNotificationTxIdx, txInpIfNotificationExcIdx, txInpIfNotificationInputIdx }
            ::= { txInputSatFeedBtsTable 1 }

        
        TxInputSatFeedBtsEntry ::=
            SEQUENCE { 
                txSatBtsDecompEnable
                    TruthValue,
                txSatBtsRegionalization
                    SwitchOnOff,
                txSatBtsPliTablePid
                    Unsigned32,
                txSatBtsNullPacketLaPid
                    Unsigned32,
                txSatBtsNullPacketLbPid
                    Unsigned32,
                txSatBtsNullPacketLcPid
                    Unsigned32
             }

        txSatBtsDecompEnable OBJECT-TYPE
            SYNTAX TruthValue
            MAX-ACCESS read-only
            STATUS obsolete
            DESCRIPTION
                "obsolete"
            ::= { txInputSatFeedBtsEntry 1 }

        
        txSatBtsRegionalization OBJECT-TYPE
            SYNTAX SwitchOnOff
            MAX-ACCESS read-write
            STATUS obsolete
            DESCRIPTION
                "obsolete.
                replaced by isdbtNitRestampingTable"
            ::= { txInputSatFeedBtsEntry 2 }

        
        txSatBtsPliTablePid OBJECT-TYPE
            SYNTAX Unsigned32 (0..8191)
            MAX-ACCESS read-write
            STATUS current
            DESCRIPTION
                "Indicates the packet id which contains the PLI table in the 
                DVB-S/S2 stream. The setting can be changed here.
                "
            ::= { txInputSatFeedBtsEntry 3 }

        
        txSatBtsNullPacketLaPid OBJECT-TYPE
            SYNTAX Unsigned32 (0..8191)
            MAX-ACCESS read-write
            STATUS current
            DESCRIPTION
                "Indicates the packet id which contains the payload for layer A. 
                The setting can be changed here.
                "
            ::= { txInputSatFeedBtsEntry 4 }

        
        txSatBtsNullPacketLbPid OBJECT-TYPE
            SYNTAX Unsigned32 (0..8191)
            MAX-ACCESS read-write
            STATUS current
            DESCRIPTION
                "Indicates the packet id which contains the payload for layer B. 
                The setting can be changed here.
                "
            ::= { txInputSatFeedBtsEntry 5 }

        
        txSatBtsNullPacketLcPid OBJECT-TYPE
            SYNTAX Unsigned32 (0..8191)
            MAX-ACCESS read-write
            STATUS current
            DESCRIPTION
                "Indicates the packet id which contains the payload for layer C. 
                The setting can be changed here.
                "
            ::= { txInputSatFeedBtsEntry 6 }

        
        txInputSatFeedExtrasTable OBJECT-TYPE
            SYNTAX SEQUENCE OF TxInputSatFeedExtrasEntry
            MAX-ACCESS not-accessible
            STATUS current
            DESCRIPTION
                "Description."
            ::= { txInputSatFeed 9 }

        
        txInputSatFeedExtrasEntry OBJECT-TYPE
            SYNTAX TxInputSatFeedExtrasEntry
            MAX-ACCESS not-accessible
            STATUS current
            DESCRIPTION
                "Description."
            INDEX { txInpIfNotificationTxIdx, txInpIfNotificationExcIdx, txInpIfNotificationInputIdx }
            ::= { txInputSatFeedExtrasTable 1 }

        
        TxInputSatFeedExtrasEntry ::=
            SEQUENCE { 
                txSatMultiStreamStatus
                    INTEGER,
                txSatMultiStreamUsedStreamId
                    Unsigned32,
                txSatPlScrambling
                    INTEGER,
                txSatPlsCode
                    Integer32,
                txSatPlsCode2
                    Integer32,
                txSatPlsCode3
                    Integer32,
                txSatCodeLoop
                    SwitchOnOff,
                txSatPlsSelect
                    INTEGER,
                txSatPlsActive
                    INTEGER,
                txSatStreamCurrentTsId
                    Unsigned32,
                txSatStreamExpectedTsId
                    Unsigned32
             }

        txSatMultiStreamStatus OBJECT-TYPE
            SYNTAX INTEGER
                {
                notFound(1),
                available(2)
                }
            MAX-ACCESS read-only
            STATUS current
            DESCRIPTION
                "Indicates, whether the sat receiver is locked to the stream 
                with the 'Used Stream ID'.
                "
            ::= { txInputSatFeedExtrasEntry 1 }

        
        txSatMultiStreamUsedStreamId OBJECT-TYPE
            SYNTAX Unsigned32 (0..255)
            MAX-ACCESS read-write
            STATUS current
            DESCRIPTION
                "Indicates which datastream shall be used. 
                The stream id can be changed here.
                "
            ::= { txInputSatFeedExtrasEntry 2 }

        
        txSatPlScrambling OBJECT-TYPE
            SYNTAX INTEGER
                {
                gold(1),
                root(2)
                }
            MAX-ACCESS read-write
            STATUS current
            DESCRIPTION
                "Indicates the method how the polynomial to descramble the 
                datastream is calculated. The setting can be changed here. 
                Physical Layer Scrambling is disabled when PL Scrambling 
                is set to 'Gold' and Code is set to '0'
                "
            ::= { txInputSatFeedExtrasEntry 3 }

        
        txSatPlsCode OBJECT-TYPE
            SYNTAX Integer32 (-1..262143)
            MAX-ACCESS read-write
            STATUS current
            DESCRIPTION
                "Indicates the decryption code. 
                This code and the method how the polynomial is calculated must 
                be identical to the settings of scrambler in playout. Up to three 
                different codes can be used. If Loop is enabled all codes will be 
                checked automatically. 
                To avoid copying the decryption code always the value -1 is 
                displayed. 
                "
            ::= { txInputSatFeedExtrasEntry 4 }

        
        txSatPlsCode2 OBJECT-TYPE
            SYNTAX Integer32 (-1..262143)
            MAX-ACCESS read-write
            STATUS current
            DESCRIPTION
                "Indicates the decryption code. 
                This code and the method how the polynomial is calculated must 
                be identical to the settings of scrambler in playout. Up to three 
                different codes can be used. If Loop is enabled all codes will be 
                checked automatically. 
                To avoid copying the decryption code always the value -1 is 
                displayed. 
                "
            ::= { txInputSatFeedExtrasEntry 5 }

        
        txSatPlsCode3 OBJECT-TYPE
            SYNTAX Integer32 (-1..262143)
            MAX-ACCESS read-write
            STATUS current
            DESCRIPTION
                "Indicates the decryption code. 
                This code and the method how the polynomial is calculated must 
                be identical to the settings of scrambler in playout. Up to three 
                different codes can be used. If Loop is enabled all codes will be 
                checked automatically. 
                To avoid copying the decryption code always the value -1 is 
                displayed. 
                "
            ::= { txInputSatFeedExtrasEntry 6 }

        
        txSatCodeLoop OBJECT-TYPE
            SYNTAX SwitchOnOff
            MAX-ACCESS read-write
            STATUS current
            DESCRIPTION
                "Indicates whether the automatic pls code scanning is active. 
                Up to three different pls codes can be used to decode the 
                transport stream. 
                "
            ::= { txInputSatFeedExtrasEntry 10 }

        
        txSatPlsSelect OBJECT-TYPE
            SYNTAX INTEGER
                {
                code1(1),
                code2(2),
                code3(3)
                }
            MAX-ACCESS read-write
            STATUS current
            DESCRIPTION
                "When automatic loop is disabled one of up to three stored
                pls codes can be selected manually. "
            ::= { txInputSatFeedExtrasEntry 11 }

        
        txSatPlsActive OBJECT-TYPE
            SYNTAX INTEGER
                {
                code1(1),
                code2(2),
                code3(3)
                }
            MAX-ACCESS read-only
            STATUS current
            DESCRIPTION
                "Indicates the used PLS code. "
            ::= { txInputSatFeedExtrasEntry 12 }

        
        txSatStreamCurrentTsId OBJECT-TYPE
            SYNTAX Unsigned32
            MAX-ACCESS read-only
            STATUS current
            DESCRIPTION
                "Indicates the ID of currently used transport stream.
                In multistream configurations the multistream number defines the active 
                transport stream.
                "
            ::= { txInputSatFeedExtrasEntry 13 }

        
        txSatStreamExpectedTsId OBJECT-TYPE
            SYNTAX Unsigned32
            MAX-ACCESS read-write
            STATUS current
            DESCRIPTION
                "Indicates which transport stream is expected. 
                Changing the transport stream will lead to a warning. 
                Setting the expected TS ID to zero suppresses a warning.
                "
            ::= { txInputSatFeedExtrasEntry 14 }

        
        txInputExgineStateTable OBJECT-TYPE
            SYNTAX SEQUENCE OF TxInputExgineStateEntry
            MAX-ACCESS not-accessible
            STATUS current
            DESCRIPTION
                "Exgine device status information."
            ::= { txInputInterfaces 7 }

        
        txInputExgineStateEntry OBJECT-TYPE
            SYNTAX TxInputExgineStateEntry
            MAX-ACCESS not-accessible
            STATUS current
            DESCRIPTION
                "An entry in the txInputExgineStateTable."
            INDEX { txInpIfNotificationTxIdx, txInpIfNotificationExcIdx }
            ::= { txInputExgineStateTable 1 }

        
        TxInputExgineStateEntry ::=
            SEQUENCE { 
                txExgineMode
                    INTEGER,
                txExgineStatus
                    NotificationState,
                txExgineMute
                    NotificationState,
                txExgineSyncInputSrc
                    INTEGER,
                txExgineSyncInputStatus
                    NotificationState,
                txExgineMpxInput
                    NotificationState,
                txExgineE2xInput
                    NotificationState,
                txExgineSupply1Status
                    NotificationState,
                txExgineSupply2Status
                    NotificationState
             }

        txExgineMode OBJECT-TYPE
            SYNTAX INTEGER
                {
                undefined(1),
                fmOnly(2),
                hybrid(3),
                extendedHybrid(4),
                fullDigital(5)
                }
            MAX-ACCESS read-only
            STATUS current
            DESCRIPTION
                "Description."
            ::= { txInputExgineStateEntry 1 }

        
        txExgineStatus OBJECT-TYPE
            SYNTAX NotificationState
            MAX-ACCESS read-only
            STATUS current
            DESCRIPTION
                "Description."
            ::= { txInputExgineStateEntry 2 }

        
        txExgineMute OBJECT-TYPE
            SYNTAX NotificationState
            MAX-ACCESS read-only
            STATUS current
            DESCRIPTION
                "Description."
            ::= { txInputExgineStateEntry 3 }

        
        txExgineSyncInputSrc OBJECT-TYPE
            SYNTAX INTEGER
                {
                undefined(1),
                internalGps(2),
                externalReference(3)
                }
            MAX-ACCESS read-only
            STATUS current
            DESCRIPTION
                "Description."
            ::= { txInputExgineStateEntry 4 }

        
        txExgineSyncInputStatus OBJECT-TYPE
            SYNTAX NotificationState
            MAX-ACCESS read-only
            STATUS current
            DESCRIPTION
                "Description."
            ::= { txInputExgineStateEntry 5 }

        
        txExgineMpxInput OBJECT-TYPE
            SYNTAX NotificationState
            MAX-ACCESS read-only
            STATUS current
            DESCRIPTION
                "Description."
            ::= { txInputExgineStateEntry 6 }

        
        txExgineE2xInput OBJECT-TYPE
            SYNTAX NotificationState
            MAX-ACCESS read-only
            STATUS current
            DESCRIPTION
                "Description."
            ::= { txInputExgineStateEntry 7 }

        
        txExgineSupply1Status OBJECT-TYPE
            SYNTAX NotificationState
            MAX-ACCESS read-only
            STATUS current
            DESCRIPTION
                "Description."
            ::= { txInputExgineStateEntry 8 }

        
        txExgineSupply2Status OBJECT-TYPE
            SYNTAX NotificationState
            MAX-ACCESS read-only
            STATUS current
            DESCRIPTION
                "Description."
            ::= { txInputExgineStateEntry 9 }

        
        txInputAutomatic OBJECT IDENTIFIER ::= { rsXx9TxObjects 4 }

        
        txInpAutoNotificationTable OBJECT-TYPE
            SYNTAX SEQUENCE OF TxInpAutoNotificationEntry
            MAX-ACCESS not-accessible
            STATUS current
            DESCRIPTION
                "The context information/configuration for the
                input automatic status notifications."
            ::= { txInputAutomatic 1 }

        
        txInpAutoNotificationEntry OBJECT-TYPE
            SYNTAX TxInpAutoNotificationEntry
            MAX-ACCESS not-accessible
            STATUS current
            DESCRIPTION
                "An entry in the txInpAutoNotificationTable."
            INDEX { txInpAutoNotificationTxIdx, txInpAutoNotificationExcIdx, txInpAutoNotificationIdx }
            ::= { txInpAutoNotificationTable 1 }

        
        TxInpAutoNotificationEntry ::=
            SEQUENCE { 
                txInpAutoNotificationTxIdx
                    IndexTransmitter,
                txInpAutoNotificationExcIdx
                    IndexAB,
                txInpAutoNotificationIdx
                    Unsigned32,
                txInpAutoNotificationName
                    INTEGER,
                txInpAutoNotificationMask
                    NotificationMask,
                txInpAutoNotificationPriority
                    NotificationPriority,
                txInpAutoNotificationState
                    NotificationState
             }

        txInpAutoNotificationTxIdx OBJECT-TYPE
            SYNTAX IndexTransmitter
            MAX-ACCESS not-accessible
            STATUS current
            DESCRIPTION
                "The transmitter index."
            ::= { txInpAutoNotificationEntry 1 }

        
        txInpAutoNotificationExcIdx OBJECT-TYPE
            SYNTAX IndexAB
            MAX-ACCESS not-accessible
            STATUS current
            DESCRIPTION
                "This index distinguishes the exiters.
                Necessary if you have dual drive transmitters."
            ::= { txInpAutoNotificationEntry 2 }

        
        txInpAutoNotificationIdx OBJECT-TYPE
            SYNTAX Unsigned32 (4000..4001)
            MAX-ACCESS not-accessible
            STATUS current
            DESCRIPTION
                "The notification number as below rsXx9TxNotifications.
                This is a helper column and therefore not-accessible."
            ::= { txInpAutoNotificationEntry 3 }

        
        txInpAutoNotificationName OBJECT-TYPE
            SYNTAX INTEGER
                {
                txInpAuto1Active(4000),
                txInpAutoState(4001)
                }
            MAX-ACCESS read-only
            STATUS current
            DESCRIPTION
                "The notification number as an enumeration.
                The enumeration correlates with the notifications under rsXx9TxNotifications."
            ::= { txInpAutoNotificationEntry 4 }

        
        txInpAutoNotificationMask OBJECT-TYPE
            SYNTAX NotificationMask
            MAX-ACCESS read-write
            STATUS current
            DESCRIPTION
                "See textual convention for details."
            ::= { txInpAutoNotificationEntry 5 }

        
        txInpAutoNotificationPriority OBJECT-TYPE
            SYNTAX NotificationPriority
            MAX-ACCESS read-write
            STATUS current
            DESCRIPTION
                "See textual convention for details."
            ::= { txInpAutoNotificationEntry 6 }

        
        txInpAutoNotificationState OBJECT-TYPE
            SYNTAX NotificationState
            MAX-ACCESS read-only
            STATUS current
            DESCRIPTION
                "See textual convention for details."
            ::= { txInpAutoNotificationEntry 7 }

        
        txInpAutoConfigurationTable OBJECT-TYPE
            SYNTAX SEQUENCE OF TxInpAutoConfigurationEntry
            MAX-ACCESS not-accessible
            STATUS current
            DESCRIPTION
                "Input automatic settings."
            ::= { txInputAutomatic 2 }

        
        txInpAutoConfigurationEntry OBJECT-TYPE
            SYNTAX TxInpAutoConfigurationEntry
            MAX-ACCESS not-accessible
            STATUS current
            DESCRIPTION
                "An entry in the txInpAutoConfigurationTable."
            INDEX { txInpAutoNotificationTxIdx, txInpAutoNotificationExcIdx }
            ::= { txInpAutoConfigurationTable 1 }

        
        TxInpAutoConfigurationEntry ::=
            SEQUENCE { 
                txInpAutoOperationMode
                    SwitchOnOff,
                txInpAutoPreferredInput
                    INTEGER,
                txInpAutoActiveInput
                    INTEGER,
                txInpAutoDirection
                    INTEGER,
                txInpAutoGuardTimeToReserve
                    Unsigned32,
                txInpAutoGuardTimeBack
                    Unsigned32,
                txInpAutoSeamlessPossible
                    TruthValue,
                txInpAutoSeamlessOpMode
                    SwitchOnOff,
                txInpAutoMaxDelayInput1To2
                    Integer32,
                txInpAutoDelayInput1To2
                    Integer32,
                txInpAutoInputFailDelay
                    Unsigned32,
                txInpAutoIfReseveFails
                    INTEGER,
                txInpAutoForceExciterChangeover
                    SwitchOnOff,
                txInpAutoMuteOnInputFail
                    SwitchOnOff,
                txInpAutoDetectLostPackets
                    SwitchOnOff,
                txInpAutoTransparentTs
                    SwitchOnOff,
                txInpAutoFailDetection
                    INTEGER
             }

        txInpAutoOperationMode OBJECT-TYPE
            SYNTAX SwitchOnOff
            MAX-ACCESS read-write
            STATUS current
            DESCRIPTION
                "Switches the input automatic on or off."
            ::= { txInpAutoConfigurationEntry 1 }

        
        txInpAutoPreferredInput OBJECT-TYPE
            SYNTAX INTEGER
                {
                input1(1),
                noPreference(2),
                input2(3)
                }
            MAX-ACCESS read-write
            STATUS current
            DESCRIPTION
                "Selects the preferred input for the input automatic.
                
                Not for FM."
            ::= { txInpAutoConfigurationEntry 2 }

        
        txInpAutoActiveInput OBJECT-TYPE
            SYNTAX INTEGER
                {
                input1(2),
                input2(3)
                }
            MAX-ACCESS read-write
            STATUS current
            DESCRIPTION
                "Used to select the active input if the automatic input signal
                switchover function is switched off.
                If the automatic switchover function is switched on,
                the input can only be switched over using this switch
                if txInpAutoPreferredInput is set to noPreference(3)
                or a switchover to the standby input has taken place.
                (The latter not for FM.)"
            ::= { txInpAutoConfigurationEntry 3 }

        
        txInpAutoDirection OBJECT-TYPE
            SYNTAX INTEGER
                {
                toReserveAndBack(1),
                toReserveOnly(2)
                }
            MAX-ACCESS read-write
            STATUS current
            DESCRIPTION
                "Used to set the operational response of the automatic switchover function:
                toReserveAndBack(1) - Following successful switchover to the standby input,
                    the automatic switchover function can also switch back automatically
                    if the signal at the standby input fails.
                toReserveOnly(2)    - The automatic switchover function switches over once
                    from the preferred input to the standby input and then assumes the
                    'not ready' state. Switching the active input over manually to the
                    preferred input reactivates the automatic switchover function."
            ::= { txInpAutoConfigurationEntry 4 }

        
        txInpAutoGuardTimeToReserve OBJECT-TYPE
            SYNTAX Unsigned32 (0..100)
            UNITS "second"
            MAX-ACCESS read-write
            STATUS current
            DESCRIPTION
                "Used to set a guard time which must elapse before the
                automatic switchover function switches over to the
                standby input if the input signal at the preferred input fails.
                The set guard time has no effect if seamless switching is possible.
                In this case, the switchover always takes place immediately without
                interruption (i.e. seamlessly)."
            ::= { txInpAutoConfigurationEntry 5 }

        
        txInpAutoGuardTimeBack OBJECT-TYPE
            SYNTAX Unsigned32 (0..100)
            UNITS "second"
            MAX-ACCESS read-write
            STATUS current
            DESCRIPTION
                "Used to set a guard time which must elapse before the
                automatic switchover function switches back to the
                preferred input if the input signal at the standby input fails.
                If seamless switching is possible, switchover always takes place
                immediately without interruption regardless of the set guard time.
                If toReserveOnly(1) was selected for txInpAutoDirection,
                the set guard time has no effect."
            ::= { txInpAutoConfigurationEntry 6 }

        
        txInpAutoSeamlessPossible OBJECT-TYPE
            SYNTAX TruthValue
            MAX-ACCESS read-only
            STATUS current
            DESCRIPTION
                "Indicates whether seamless switching of the input signal is possible.
                false(2) (not possible) always appears if only one input signal is
                supplied or in cases where two different data streams are present at
                the two inputs.
                If seamless switching is possible, it always takes place immediately
                when required, regardless of whether txInpAutoGuardTimeToReserve or
                txInpAutoGuardTimeBack has been set."
            ::= { txInpAutoConfigurationEntry 7 }

        
        txInpAutoSeamlessOpMode OBJECT-TYPE
            SYNTAX SwitchOnOff
            MAX-ACCESS read-write
            STATUS current
            DESCRIPTION
                "Activates/deactivates seamless switchover of the input signal."
            ::= { txInpAutoConfigurationEntry 8 }

        
        txInpAutoMaxDelayInput1To2 OBJECT-TYPE
            SYNTAX Integer32 (0..2000)
            UNITS "milli second"
            MAX-ACCESS read-write
            STATUS obsolete
            DESCRIPTION
                "Absolute maximum delay between logical input 1 and logical input 2."
            ::= { txInpAutoConfigurationEntry 9 }

        
        txInpAutoDelayInput1To2 OBJECT-TYPE
            SYNTAX Integer32
            UNITS "milli second"
            MAX-ACCESS read-only
            STATUS current
            DESCRIPTION
                "The current delay between logical input 1 and logical input 2.
                "
            ::= { txInpAutoConfigurationEntry 10 }

        
        txInpAutoInputFailDelay OBJECT-TYPE
            SYNTAX Unsigned32 (0..600)
            UNITS "second"
            MAX-ACCESS read-write
            STATUS current
            DESCRIPTION
                "The length of the checkout time which must expire after detection
                of an input signal fault before the exciter displays a fault.
                If a short checkout time is set, the system can quickly switch over
                to a standby exciter if all input signals of the exciter fail.
                If a long checkout time is set, there will be enough time in the event
                of a fault to switch to an alternative feed path so that the exciter is
                prevented from switching over to a redundancy component.
                
                Not for band II."
            ::= { txInpAutoConfigurationEntry 11 }

        
        txInpAutoIfReseveFails OBJECT-TYPE
            SYNTAX INTEGER
                {
                nothing(1),
                warn(2)
                }
            MAX-ACCESS read-write
            STATUS current
            DESCRIPTION
                "Determine whether the signal at the standby input is to be monitored.
                If the transmitter is operated with only one input signal or the
                standby input is connected only temporarily,
                nothing(1) must be selected to not generate a warning.
                If two redundant input signals are normally supplied to the transmitter,
                warn(2) must be selected."
            ::= { txInpAutoConfigurationEntry 12 }

        
        txInpAutoForceExciterChangeover OBJECT-TYPE
            SYNTAX SwitchOnOff
            MAX-ACCESS read-write
            STATUS current
            DESCRIPTION
                "Determine whether switchover to another redundant exciter is to take place
                if the input signal fails.
                This function is available for all redundancy systems (dual drive,
                backup exciter and n+1).
                on(1)  - an exciter fault is signaled to the higher-level redundancy
                         control unit which decides whether to switch over to another
                         exciter or transmitter.
                off(2) - no switchover takes place."
            ::= { txInpAutoConfigurationEntry 13 }

        
        txInpAutoMuteOnInputFail OBJECT-TYPE
            SYNTAX SwitchOnOff
            MAX-ACCESS read-write
            STATUS current
            DESCRIPTION
                "Determine whether the output signal of the exciter is to be shut down
                if the input signal of all available inputs fails, or whether
                'null packets' are to be sent.
                This switch is available in multiple-frequency networks (MFN) only.
                In single-frequency networks (SFN) and using TV standard ISDB-T,
                the exciter will always mute if no decodable input signal is fed.
                
                Not for FM."
            ::= { txInpAutoConfigurationEntry 14 }

        
        txInpAutoDetectLostPackets OBJECT-TYPE
            SYNTAX SwitchOnOff
            MAX-ACCESS read-write
            STATUS current
            DESCRIPTION
                "Description."
            ::= { txInpAutoConfigurationEntry 15 }

        
        txInpAutoTransparentTs OBJECT-TYPE
            SYNTAX SwitchOnOff
            MAX-ACCESS read-write
            STATUS current
            DESCRIPTION
                "Description."
            ::= { txInpAutoConfigurationEntry 16 }

        
        txInpAutoFailDetection OBJECT-TYPE
            SYNTAX INTEGER
                {
                normal(1),
                fast(2)
                }
            MAX-ACCESS read-write
            STATUS current
            DESCRIPTION
                "Indicates how quick the exciter input reacts on missing data packets. 
                
                normal(1): bursts in transport stream are processed without error indication 
                  (recommended for IP feed). 
                fast(2): this setting decreases the reaction time in case of a loss of input signal. 
                  It can be used when a continous datastream at the exciter input is guaranteed.
                "
            ::= { txInpAutoConfigurationEntry 17 }

        
        txFrequencyRegulation OBJECT IDENTIFIER ::= { rsXx9TxObjects 5 }

        
        txFrqRegNotificationTable OBJECT-TYPE
            SYNTAX SEQUENCE OF TxFrqRegNotificationEntry
            MAX-ACCESS not-accessible
            STATUS current
            DESCRIPTION
                "The context information/configuration for the
                SFN status notifications."
            ::= { txFrequencyRegulation 1 }

        
        txFrqRegNotificationEntry OBJECT-TYPE
            SYNTAX TxFrqRegNotificationEntry
            MAX-ACCESS not-accessible
            STATUS current
            DESCRIPTION
                "An entry in the txSfnNotificationTable."
            INDEX { txFrqRegNotificationTxIdx, txFrqRegNotificationExcIdx, txFrqRegNotificationIdx }
            ::= { txFrqRegNotificationTable 1 }

        
        TxFrqRegNotificationEntry ::=
            SEQUENCE { 
                txFrqRegNotificationTxIdx
                    IndexTransmitter,
                txFrqRegNotificationExcIdx
                    IndexAB,
                txFrqRegNotificationIdx
                    Unsigned32,
                txFrqRegNotificationName
                    INTEGER,
                txFrqRegNotificationMask
                    NotificationMask,
                txFrqRegNotificationPriority
                    NotificationPriority,
                txFrqRegNotificationState
                    NotificationState
             }

        txFrqRegNotificationTxIdx OBJECT-TYPE
            SYNTAX IndexTransmitter
            MAX-ACCESS not-accessible
            STATUS current
            DESCRIPTION
                "The transmitter index."
            ::= { txFrqRegNotificationEntry 1 }

        
        txFrqRegNotificationExcIdx OBJECT-TYPE
            SYNTAX IndexAB
            MAX-ACCESS not-accessible
            STATUS current
            DESCRIPTION
                "This index distinguishes the exiters.
                Necessary if you have dual drive transmitters."
            ::= { txFrqRegNotificationEntry 2 }

        
        txFrqRegNotificationIdx OBJECT-TYPE
            SYNTAX Unsigned32 (5000..5004)
            MAX-ACCESS not-accessible
            STATUS current
            DESCRIPTION
                "The notification number as below rsXx9TxNotifications.
                This is a helper column and therefore not-accessible."
            ::= { txFrqRegNotificationEntry 3 }

        
        txFrqRegNotificationName OBJECT-TYPE
            SYNTAX INTEGER
                {
                txFrqRegSummary(5000),
                txFrqRegCurrentSource(5001),
                txFrqRegSourceExtRef(5002),
                txFrqRegSourceExtPPS(5003),
                txFrqRegSourceIntGPS(5004)
                }
            MAX-ACCESS read-only
            STATUS current
            DESCRIPTION
                "The notification number as an enumeration.
                The enumeration correlates with the notifications under rsXx9TxNotifications."
            ::= { txFrqRegNotificationEntry 4 }

        
        txFrqRegNotificationMask OBJECT-TYPE
            SYNTAX NotificationMask
            MAX-ACCESS read-write
            STATUS current
            DESCRIPTION
                "See textual convention for details."
            ::= { txFrqRegNotificationEntry 5 }

        
        txFrqRegNotificationPriority OBJECT-TYPE
            SYNTAX NotificationPriority
            MAX-ACCESS read-write
            STATUS current
            DESCRIPTION
                "See textual convention for details."
            ::= { txFrqRegNotificationEntry 6 }

        
        txFrqRegNotificationState OBJECT-TYPE
            SYNTAX NotificationState
            MAX-ACCESS read-only
            STATUS current
            DESCRIPTION
                "See textual convention for details."
            ::= { txFrqRegNotificationEntry 7 }

        
        txFrqRegStateTable OBJECT-TYPE
            SYNTAX SEQUENCE OF TxFrqRegStateEntry
            MAX-ACCESS not-accessible
            STATUS current
            DESCRIPTION
                "Frequency regulation status."
            ::= { txFrequencyRegulation 2 }

        
        txFrqRegStateEntry OBJECT-TYPE
            SYNTAX TxFrqRegStateEntry
            MAX-ACCESS not-accessible
            STATUS current
            DESCRIPTION
                "An entry in the txSfnFreqRegulationTable."
            INDEX { txFrqRegNotificationTxIdx, txFrqRegNotificationExcIdx }
            ::= { txFrqRegStateTable 1 }

        
        TxFrqRegStateEntry ::=
            SEQUENCE { 
                txFrqRegStateCurrentSource
                    INTEGER,
                txFrqRegStateController
                    INTEGER,
                txFrqRegStateCurrentControllerMode
                    ControllerMode
             }

        txFrqRegStateCurrentSource OBJECT-TYPE
            SYNTAX INTEGER
                {
                manual(1),
                external5MHz(2),
                external10MHz(3),
                externalPPS(4),
                internalGPS(5)
                }
            MAX-ACCESS read-only
            STATUS current
            DESCRIPTION
                "The current source for frequency synchronization."
            ::= { txFrqRegStateEntry 1 }

        
        txFrqRegStateController OBJECT-TYPE
            SYNTAX INTEGER
                {
                unknown(1),
                inaccurate(2),
                good(3),
                standsGuardTime(4)
                }
            MAX-ACCESS read-only
            STATUS current
            DESCRIPTION
                "The precision of frequency regulation."
            ::= { txFrqRegStateEntry 2 }

        
        txFrqRegStateCurrentControllerMode OBJECT-TYPE
            SYNTAX ControllerMode
            MAX-ACCESS read-only
            STATUS current
            DESCRIPTION
                "Description."
            ::= { txFrqRegStateEntry 3 }

        
        txFrqRegSetupTable OBJECT-TYPE
            SYNTAX SEQUENCE OF TxFrqRegSetupEntry
            MAX-ACCESS not-accessible
            STATUS current
            DESCRIPTION
                "Frequency regulation configuration."
            ::= { txFrequencyRegulation 3 }

        
        txFrqRegSetupEntry OBJECT-TYPE
            SYNTAX TxFrqRegSetupEntry
            MAX-ACCESS not-accessible
            STATUS current
            DESCRIPTION
                "An entry in the txFrqRegSetupTable."
            INDEX { txFrqRegNotificationTxIdx, txFrqRegNotificationExcIdx }
            ::= { txFrqRegSetupTable 1 }

        
        TxFrqRegSetupEntry ::=
            SEQUENCE { 
                txFrqRegSetupSource
                    INTEGER,
                txFrqRegSetupControllerMode
                    ControllerMode,
                txFrqRegSetupRefFailPermissionTime
                    Unsigned32,
                txFrqRegSetupMuteOnFail
                    INTEGER,
                txFrqRegSetupManualOcxoAdjust
                    Unsigned32,
                txFrqRegSetupMonitor
                    INTEGER
             }

        txFrqRegSetupSource OBJECT-TYPE
            SYNTAX INTEGER
                {
                manual(1),
                external5MHz(2),
                external10MHz(3),
                externalPPS(4),
                internalGPS(5),
                auto(6)
                }
            MAX-ACCESS read-write
            STATUS current
            DESCRIPTION
                "The appropriate signal source for the reference frequency
                may be determined automatically or defined by this value.
                If auto(6) is choosen and several signal sources are available,
                an external reference will be preferred over internal GPS.
                If manual(1) is choosen the OCXO may be set with
                txSfnFreqRegManualOcxoAdjust."
            ::= { txFrqRegSetupEntry 1 }

        
        txFrqRegSetupControllerMode OBJECT-TYPE
            SYNTAX ControllerMode
            MAX-ACCESS read-write
            STATUS current
            DESCRIPTION
                "When using an external 1PPS reference source with high 
                jitter, activating this function can provide better frequency 
                stability. For 'good' reference signals, this function should be 
                disabled, as the regulator takes significantly longer to attain its 
                maximum frequency stability.
                "
            ::= { txFrqRegSetupEntry 2 }

        
        txFrqRegSetupRefFailPermissionTime OBJECT-TYPE
            SYNTAX Unsigned32 (0..24)
            UNITS "hour"
            MAX-ACCESS read-write
            STATUS current
            DESCRIPTION
                "Defines how many hours after loss of reference
                signal processing will go on."
            ::= { txFrqRegSetupEntry 3 }

        
        txFrqRegSetupMuteOnFail OBJECT-TYPE
            SYNTAX INTEGER
                {
                never(1),
                onlyAtStartup(2),
                ifGuardTimeExpires(3)
                }
            MAX-ACCESS read-write
            STATUS current
            DESCRIPTION
                "Determines performance in case of reference loss.
                never(1) - muting is never done
                onlyAtStartup(2) - 
                ifGuardTimeExpires(3) - muting is done if reference loss lasts more
                                        than txSfnFreqRegRefFailPermissionTime"
            ::= { txFrqRegSetupEntry 4 }

        
        txFrqRegSetupManualOcxoAdjust OBJECT-TYPE
            SYNTAX Unsigned32 (0..65535)
            MAX-ACCESS read-write
            STATUS current
            DESCRIPTION
                "Enables adjustment of the internal crystal oszillator."
            ::= { txFrqRegSetupEntry 5 }

        
        txFrqRegSetupMonitor OBJECT-TYPE
            SYNTAX INTEGER
                {
                off(1),
                internal5MHz(2),
                internal10MHz(3),
                internal1PPS(4),
                internalGPS(5),
                currentSource(6),
                cofdmSync(7)
                }
            MAX-ACCESS read-write
            STATUS current
            DESCRIPTION
                "Selects the signal for the monitor out connector (X24).
                
                cofdmSync(7) - a synchronous signal at start of a DAB COFDM frame"
            ::= { txFrqRegSetupEntry 6 }

        
        txSFN OBJECT IDENTIFIER ::= { rsXx9TxObjects 6 }

        
        txSfnNotificationTable OBJECT-TYPE
            SYNTAX SEQUENCE OF TxSfnNotificationEntry
            MAX-ACCESS not-accessible
            STATUS current
            DESCRIPTION
                "The context information/configuration for the
                SFN status notifications."
            ::= { txSFN 1 }

        
        txSfnNotificationEntry OBJECT-TYPE
            SYNTAX TxSfnNotificationEntry
            MAX-ACCESS not-accessible
            STATUS current
            DESCRIPTION
                "An entry in the txSfnNotificationTable."
            INDEX { txSfnNotificationTxIdx, txSfnNotificationExcIdx, txSfnNotificationIdx }
            ::= { txSfnNotificationTable 1 }

        
        TxSfnNotificationEntry ::=
            SEQUENCE { 
                txSfnNotificationTxIdx
                    IndexTransmitter,
                txSfnNotificationExcIdx
                    IndexAB,
                txSfnNotificationIdx
                    Unsigned32,
                txSfnNotificationName
                    INTEGER,
                txSfnNotificationMask
                    NotificationMask,
                txSfnNotificationPriority
                    NotificationPriority,
                txSfnNotificationState
                    NotificationState
             }

        txSfnNotificationTxIdx OBJECT-TYPE
            SYNTAX IndexTransmitter
            MAX-ACCESS not-accessible
            STATUS current
            DESCRIPTION
                "The transmitter index."
            ::= { txSfnNotificationEntry 1 }

        
        txSfnNotificationExcIdx OBJECT-TYPE
            SYNTAX IndexAB
            MAX-ACCESS not-accessible
            STATUS current
            DESCRIPTION
                "This index distinguishes the exiters.
                Necessary if you have dual drive transmitters."
            ::= { txSfnNotificationEntry 2 }

        
        txSfnNotificationIdx OBJECT-TYPE
            SYNTAX Unsigned32 (6000)
            MAX-ACCESS not-accessible
            STATUS current
            DESCRIPTION
                "The notification number as below rsXx9TxNotifications.
                This is a helper column and therefore not-accessible."
            ::= { txSfnNotificationEntry 3 }

        
        txSfnNotificationName OBJECT-TYPE
            SYNTAX INTEGER { txSfnSummary(6000) }
            MAX-ACCESS read-only
            STATUS current
            DESCRIPTION
                "The notification number as an enumeration.
                The enumeration correlates with the notifications under rsXx9TxNotifications."
            ::= { txSfnNotificationEntry 4 }

        
        txSfnNotificationMask OBJECT-TYPE
            SYNTAX NotificationMask
            MAX-ACCESS read-write
            STATUS current
            DESCRIPTION
                "See textual convention for details."
            ::= { txSfnNotificationEntry 5 }

        
        txSfnNotificationPriority OBJECT-TYPE
            SYNTAX NotificationPriority
            MAX-ACCESS read-write
            STATUS current
            DESCRIPTION
                "See textual convention for details."
            ::= { txSfnNotificationEntry 6 }

        
        txSfnNotificationState OBJECT-TYPE
            SYNTAX NotificationState
            MAX-ACCESS read-only
            STATUS current
            DESCRIPTION
                "See textual convention for details."
            ::= { txSfnNotificationEntry 7 }

        
        txSfnStateTable OBJECT-TYPE
            SYNTAX SEQUENCE OF TxSfnStateEntry
            MAX-ACCESS not-accessible
            STATUS current
            DESCRIPTION
                "Time synchronization status."
            ::= { txSFN 2 }

        
        txSfnStateEntry OBJECT-TYPE
            SYNTAX TxSfnStateEntry
            MAX-ACCESS not-accessible
            STATUS current
            DESCRIPTION
                "An entry in the txSfnTimeSyncTable."
            INDEX { txSfnNotificationTxIdx, txSfnNotificationExcIdx }
            ::= { txSfnStateTable 1 }

        
        TxSfnStateEntry ::=
            SEQUENCE { 
                txSfnStateInternalPpsValid
                    TruthValue,
                txSfnStateTransmissionInTime
                    INTEGER,
                txSfnStateNetworkDelay
                    Unsigned32,
                txSfnStateProcessingTime
                    Unsigned32,
                txSfnStateDynamicDelay
                    Unsigned32,
                txSfnStateTotalDelay
                    Unsigned32,
                txSfnStateMaximumDelay
                    Unsigned32,
                txSfnStateDispatchTime
                    Unsigned32,
                txSfnStatePPS
                    INTEGER,
                txSfnStateSFN
                    INTEGER,
                txSfnStateTimestampState
                    INTEGER
             }

        txSfnStateInternalPpsValid OBJECT-TYPE
            SYNTAX TruthValue
            MAX-ACCESS read-only
            STATUS current
            DESCRIPTION
                "Shows whether the internal generated PPS is
                phase synchronous to frequency regulation."
            ::= { txSfnStateEntry 1 }

        
        txSfnStateTransmissionInTime OBJECT-TYPE
            SYNTAX INTEGER
                {
                unknown(2),
                outOfTime(4),
                inTime(5)
                }
            MAX-ACCESS read-only
            STATUS current
            DESCRIPTION
                "Indicates whether or not the fed signal can be transmitted in a 
                time-synchronous manner. If an error message is displayed, 
                check the reference feed of the Time Synchronization and the 
                Frequency Regulation."
            ::= { txSfnStateEntry 2 }

        
        txSfnStateNetworkDelay OBJECT-TYPE
            SYNTAX Unsigned32
            UNITS "1/10 micro second"
            MAX-ACCESS read-only
            STATUS current
            DESCRIPTION
                "Delivery time of signal from SFN adapter till transmitter input.
                
                For DVB-T, ISDB-T, DTMB, ATSC only."
            ::= { txSfnStateEntry 3 }

        
        txSfnStateProcessingTime OBJECT-TYPE
            SYNTAX Unsigned32
            UNITS "1/10 micro second"
            MAX-ACCESS read-only
            STATUS current
            DESCRIPTION
                "Time used for internal signal processing.
                
                
                For DAB, this indicates the minimal transit time of the signal through 
                the transmitter. The transit time is determined by the signal 
                processing in the Channel Encoder (COFDM) and is depending on the 
                set DAB mode.
                "
            ::= { txSfnStateEntry 4 }

        
        txSfnStateDynamicDelay OBJECT-TYPE
            SYNTAX Unsigned32
            UNITS "1/10 micro second"
            MAX-ACCESS read-only
            STATUS current
            DESCRIPTION
                "SFN controlled time delay for matching
                transmitting point in time exactly."
            ::= { txSfnStateEntry 5 }

        
        txSfnStateTotalDelay OBJECT-TYPE
            SYNTAX Unsigned32
            UNITS "1/10 micro second"
            MAX-ACCESS read-only
            STATUS current
            DESCRIPTION
                "Overall retention time through transmitter:
                sum of txSfnTimeSyncProcessingTime and txSfnTimeSyncDynamicDelay"
            ::= { txSfnStateEntry 6 }

        
        txSfnStateMaximumDelay OBJECT-TYPE
            SYNTAX Unsigned32
            UNITS "1/10 micro second"
            MAX-ACCESS read-only
            STATUS current
            DESCRIPTION
                "Time taken for the signal to travel from the play-out center
                to the transmitter antenna for regular transmission.
                This delay is set in the SFN adapter and is the default
                for all transmitters in a dynamic SFN.
                
                For DVB-T, ISDB-T, DTMB, ATSC only."
            ::= { txSfnStateEntry 7 }

        
        txSfnStateDispatchTime OBJECT-TYPE
            SYNTAX Unsigned32
            UNITS "1/10 micro second"
            MAX-ACCESS read-only
            STATUS current
            DESCRIPTION
                "Time taken for the signal to travel from the play-out center
                to the transmitter antenna for real transmission.
                This delay corresponds to the default Maximum Delay for all transmitters
                in a SFN plus tranmitter specific Static Delay Offset
                plus Tx Time Offset (if available).
                
                For DVB-T, ISDB-T, DTMB, ATSC only."
            ::= { txSfnStateEntry 8 }

        
        txSfnStatePPS OBJECT-TYPE
            SYNTAX INTEGER
                {
                notStated(1),
                missing(2),
                holdoverExpired(3),
                holdover(4),
                ok(5)
                }
            MAX-ACCESS read-only
            STATUS current
            DESCRIPTION
                "Description."
            ::= { txSfnStateEntry 9 }

        
        txSfnStateSFN OBJECT-TYPE
            SYNTAX INTEGER
                {
                notStated(1),
                sfnResync(2),
                noTimeReference(3),
                inTime(4),
                noTimeInformation(5),
                wrongSfnTimeSetup(6),
                wrongFreqRefSource(7)
                }
            MAX-ACCESS read-only
            STATUS current
            DESCRIPTION
                "Shows whether the fed signal may be transmitted time synchronous.
                "
            ::= { txSfnStateEntry 10 }

        
        txSfnStateTimestampState OBJECT-TYPE
            SYNTAX INTEGER
                {
                off(1),
                none(2),
                null(3),
                relative(4),
                absolute(5),
                multiple(6)
                }
            MAX-ACCESS read-only
            STATUS current
            DESCRIPTION
                "Description."
            ::= { txSfnStateEntry 11 }

        
        txSfnSetupTable OBJECT-TYPE
            SYNTAX SEQUENCE OF TxSfnSetupEntry
            MAX-ACCESS not-accessible
            STATUS current
            DESCRIPTION
                "Time synchronization configuration."
            ::= { txSFN 3 }

        
        txSfnSetupEntry OBJECT-TYPE
            SYNTAX TxSfnSetupEntry
            MAX-ACCESS not-accessible
            STATUS current
            DESCRIPTION
                "An entry in the txSfnSetupTable."
            INDEX { txSfnNotificationTxIdx, txSfnNotificationExcIdx }
            ::= { txSfnSetupTable 1 }

        
        TxSfnSetupEntry ::=
            SEQUENCE { 
                txSfnSetupSource
                    INTEGER,
                txSfnSetupSFN
                    INTEGER,
                txSfnSetupMaxDeviation
                    Unsigned32,
                txSfnSetupStaticDelay
                    Integer32
             }

        txSfnSetupSource OBJECT-TYPE
            SYNTAX INTEGER
                {
                externalPPS(4),
                internalGPS(5)
                }
            MAX-ACCESS read-write
            STATUS current
            DESCRIPTION
                "The suitable signal source for synchronizing the time of transmission."
            ::= { txSfnSetupEntry 1 }

        
        txSfnSetupSFN OBJECT-TYPE
            SYNTAX INTEGER
                {
                undefined(1),
                off(2),
                on(3)
                }
            MAX-ACCESS read-write
            STATUS current
            DESCRIPTION
                "Selects mode of time synchronization:
                off(2) - MFN
                on(3)  - SFN
                
                for ISDB-T, please use isdbtCfgNetworkMode instead
                for DTMB, please use dtmbConfigurationNetworkMode instead
                for DAB, please use dabSetupSfnSync instead"
            ::= { txSfnSetupEntry 2 }

        
        txSfnSetupMaxDeviation OBJECT-TYPE
            SYNTAX Unsigned32 (1..1000)
            UNITS "1/10 micro second"
            MAX-ACCESS read-write
            STATUS current
            DESCRIPTION
                "Maximum admissible deviation for transmitting point in time."
            ::= { txSfnSetupEntry 3 }

        
        txSfnSetupStaticDelay OBJECT-TYPE
            SYNTAX Integer32 (-100000000..100000000)
            UNITS "1/10 micro second"
            MAX-ACCESS read-write
            STATUS current
            DESCRIPTION
                "Positive or negative offset transferred in the MIP (DVB-T) respectively 
                in IIP (ISDB-T) for the individual transmitter location of the time of 
                transmission relative to the regular time of transmission preset by 
                the Maximum Delay. This delay is only displayed and activated if the 
                Tx automatic function (DVB-T) respectively Equipment Control (ISDB-T) 
                is active. If Tx Offset Delay and Static Delay are present at the same 
                time, their effects are added together.
                "
            ::= { txSfnSetupEntry 4 }

        
        txGPS OBJECT IDENTIFIER ::= { rsXx9TxObjects 7 }

        
        txPrecorrection OBJECT IDENTIFIER ::= { rsXx9TxObjects 8 }

        
        txPrecorrNotificationTable OBJECT-TYPE
            SYNTAX SEQUENCE OF TxPrecorrNotificationEntry
            MAX-ACCESS not-accessible
            STATUS current
            DESCRIPTION
                "The context information/configuration for the
                precorrection status notifications."
            ::= { txPrecorrection 1 }

        
        txPrecorrNotificationEntry OBJECT-TYPE
            SYNTAX TxPrecorrNotificationEntry
            MAX-ACCESS not-accessible
            STATUS current
            DESCRIPTION
                "An entry in the txPrecorrNotificationTable."
            INDEX { txPrecorrNotificationTxIdx, txPrecorrNotificationExcIdx, txPrecorrNotificationIdx }
            ::= { txPrecorrNotificationTable 1 }

        
        TxPrecorrNotificationEntry ::=
            SEQUENCE { 
                txPrecorrNotificationTxIdx
                    IndexTransmitter,
                txPrecorrNotificationExcIdx
                    IndexAB,
                txPrecorrNotificationIdx
                    Unsigned32,
                txPrecorrNotificationName
                    INTEGER,
                txPrecorrNotificationMask
                    NotificationMask,
                txPrecorrNotificationPriority
                    NotificationPriority,
                txPrecorrNotificationState
                    NotificationState
             }

        txPrecorrNotificationTxIdx OBJECT-TYPE
            SYNTAX IndexTransmitter
            MAX-ACCESS not-accessible
            STATUS current
            DESCRIPTION
                "The transmitter index."
            ::= { txPrecorrNotificationEntry 1 }

        
        txPrecorrNotificationExcIdx OBJECT-TYPE
            SYNTAX IndexAB
            MAX-ACCESS not-accessible
            STATUS current
            DESCRIPTION
                "This index distinguishes the exiters.
                Necessary if you have dual drive transmitters."
            ::= { txPrecorrNotificationEntry 2 }

        
        txPrecorrNotificationIdx OBJECT-TYPE
            SYNTAX Unsigned32 (8000..8002)
            MAX-ACCESS not-accessible
            STATUS current
            DESCRIPTION
                "The notification number as below rsXx9TxNotifications.
                This is a helper column and therefore not-accessible."
            ::= { txPrecorrNotificationEntry 3 }

        
        txPrecorrNotificationName OBJECT-TYPE
            SYNTAX INTEGER
                {
                txPrecorrLinSummary(8000),
                txPrecorrNonLinSummary(8001),
                txPrecorrMerState(8002)
                }
            MAX-ACCESS read-only
            STATUS current
            DESCRIPTION
                "The notification number as an enumeration.
                The enumeration correlates with the notifications under rsXx9TxNotifications."
            ::= { txPrecorrNotificationEntry 4 }

        
        txPrecorrNotificationMask OBJECT-TYPE
            SYNTAX NotificationMask
            MAX-ACCESS read-write
            STATUS current
            DESCRIPTION
                "See textual convention for details."
            ::= { txPrecorrNotificationEntry 5 }

        
        txPrecorrNotificationPriority OBJECT-TYPE
            SYNTAX NotificationPriority
            MAX-ACCESS read-write
            STATUS current
            DESCRIPTION
                "See textual convention for details."
            ::= { txPrecorrNotificationEntry 6 }

        
        txPrecorrNotificationState OBJECT-TYPE
            SYNTAX NotificationState
            MAX-ACCESS read-only
            STATUS current
            DESCRIPTION
                "See textual convention for details."
            ::= { txPrecorrNotificationEntry 7 }

        
        txPrecorrectionLinear OBJECT IDENTIFIER ::= { txPrecorrection 2 }

        
        txPrecorrLinStateTable OBJECT-TYPE
            SYNTAX SEQUENCE OF TxPrecorrLinStateEntry
            MAX-ACCESS not-accessible
            STATUS current
            DESCRIPTION
                "Linear precorrection state information."
            ::= { txPrecorrectionLinear 1 }

        
        txPrecorrLinStateEntry OBJECT-TYPE
            SYNTAX TxPrecorrLinStateEntry
            MAX-ACCESS not-accessible
            STATUS current
            DESCRIPTION
                "An entry in the txPrecorrLinStateTable."
            INDEX { txPrecorrLinStateTxIdx, txPrecorrLinStateExcIdx }
            ::= { txPrecorrLinStateTable 1 }

        
        TxPrecorrLinStateEntry ::=
            SEQUENCE { 
                txPrecorrLinStateTxIdx
                    IndexTransmitter,
                txPrecorrLinStateExcIdx
                    IndexAB,
                txPrecorrLinStateStatus
                    PrecorrectionState,
                txPrecorrLinStateSignalLevel
                    PrecorrectionSignalLevel,
                txPrecorrLinStateAmplitudeRipple
                    Integer32,
                txPrecorrLinStateGroupDelayRipple
                    Integer32,
                txPrecorrLinStateAmplitudeRippleLimit
                    NotificationState,
                txPrecorrLinStateGroupDelayRippleLimit
                    NotificationState
             }

        txPrecorrLinStateTxIdx OBJECT-TYPE
            SYNTAX IndexTransmitter
            MAX-ACCESS not-accessible
            STATUS current
            DESCRIPTION
                "The transmitter index."
            ::= { txPrecorrLinStateEntry 1 }

        
        txPrecorrLinStateExcIdx OBJECT-TYPE
            SYNTAX IndexAB
            MAX-ACCESS not-accessible
            STATUS current
            DESCRIPTION
                "This index distinguishes the exiters.
                Necessary if you have dual drive transmitters."
            ::= { txPrecorrLinStateEntry 2 }

        
        txPrecorrLinStateStatus OBJECT-TYPE
            SYNTAX PrecorrectionState
            MAX-ACCESS read-only
            STATUS current
            DESCRIPTION
                "Linear precorrection state.
                see textual convention"
            ::= { txPrecorrLinStateEntry 3 }

        
        txPrecorrLinStateSignalLevel OBJECT-TYPE
            SYNTAX PrecorrectionSignalLevel
            MAX-ACCESS read-only
            STATUS current
            DESCRIPTION
                "see textual convention"
            ::= { txPrecorrLinStateEntry 4 }

        
        txPrecorrLinStateAmplitudeRipple OBJECT-TYPE
            SYNTAX Integer32
            UNITS "milli Bel"
            MAX-ACCESS read-only
            STATUS current
            DESCRIPTION
                "achieved residual ripple for amplitude"
            ::= { txPrecorrLinStateEntry 5 }

        
        txPrecorrLinStateGroupDelayRipple OBJECT-TYPE
            SYNTAX Integer32
            UNITS "1/10 nano second"
            MAX-ACCESS read-only
            STATUS current
            DESCRIPTION
                "achieved residual ripple for group delay"
            ::= { txPrecorrLinStateEntry 6 }

        
        txPrecorrLinStateAmplitudeRippleLimit OBJECT-TYPE
            SYNTAX NotificationState
            MAX-ACCESS read-only
            STATUS current
            DESCRIPTION
                "off(2)     - precorrection with this limit was successful
                             or limit is not checked
                warning(4) - limit is not reachable"
            ::= { txPrecorrLinStateEntry 7 }

        
        txPrecorrLinStateGroupDelayRippleLimit OBJECT-TYPE
            SYNTAX NotificationState
            MAX-ACCESS read-only
            STATUS current
            DESCRIPTION
                "off(2)     - precorrection with this limit was successful
                             or limit is not checked
                warning(4) - limit is not reachable"
            ::= { txPrecorrLinStateEntry 8 }

        
        txPrecorrLinSetupTable OBJECT-TYPE
            SYNTAX SEQUENCE OF TxPrecorrLinSetupEntry
            MAX-ACCESS not-accessible
            STATUS current
            DESCRIPTION
                "Linear precorrection settings."
            ::= { txPrecorrectionLinear 2 }

        
        txPrecorrLinSetupEntry OBJECT-TYPE
            SYNTAX TxPrecorrLinSetupEntry
            MAX-ACCESS not-accessible
            STATUS current
            DESCRIPTION
                "An entry in the txPrecorrLinSetupTable."
            AUGMENTS { txPrecorrLinStateEntry }
            ::= { txPrecorrLinSetupTable 1 }

        
        TxPrecorrLinSetupEntry ::=
            SEQUENCE { 
                txPrecorrLinSetupOpMode
                    PrecorrectionOperationMode,
                txPrecorrLinSetupReset
                    Trigger,
                txPrecorrLinSetupAmplitudeRippleLimit
                    Unsigned32,
                txPrecorrLinSetupGroupDelayRippleLimit
                    Unsigned32,
                txPrecorrLinSetupEquipmentSlope
                    Integer32
             }

        txPrecorrLinSetupOpMode OBJECT-TYPE
            SYNTAX PrecorrectionOperationMode
            MAX-ACCESS read-write
            STATUS current
            DESCRIPTION
                "see textual convention"
            ::= { txPrecorrLinSetupEntry 1 }

        
        txPrecorrLinSetupReset OBJECT-TYPE
            SYNTAX Trigger
            MAX-ACCESS read-write
            STATUS current
            DESCRIPTION
                "Reset of predistorter leads to recalculation of
                precorrection curve. Meanwhile precorrection is not active."
            ::= { txPrecorrLinSetupEntry 2 }

        
        txPrecorrLinSetupAmplitudeRippleLimit OBJECT-TYPE
            SYNTAX Unsigned32 (1..20)
            UNITS "centi Bel"
            MAX-ACCESS read-write
            STATUS current
            DESCRIPTION
                "Desired maximal amplitude ripple on filter output."
            ::= { txPrecorrLinSetupEntry 3 }

        
        txPrecorrLinSetupGroupDelayRippleLimit OBJECT-TYPE
            SYNTAX Unsigned32 (10..500)
            UNITS "nano second"
            MAX-ACCESS read-write
            STATUS current
            DESCRIPTION
                "Desired maximal group delay ripple on filter output."
            ::= { txPrecorrLinSetupEntry 4 }

        
        txPrecorrLinSetupEquipmentSlope OBJECT-TYPE
            SYNTAX Integer32 (-100..100)
            UNITS "milli Bel"
            MAX-ACCESS read-write
            STATUS current
            DESCRIPTION
                "Description"
            ::= { txPrecorrLinSetupEntry 5 }

        
        txPrecorrectionNonLinear OBJECT IDENTIFIER ::= { txPrecorrection 3 }

        
        txPrecorrNonLinStateTable OBJECT-TYPE
            SYNTAX SEQUENCE OF TxPrecorrNonLinStateEntry
            MAX-ACCESS not-accessible
            STATUS current
            DESCRIPTION
                "Non linear precorrection state information."
            ::= { txPrecorrectionNonLinear 1 }

        
        txPrecorrNonLinStateEntry OBJECT-TYPE
            SYNTAX TxPrecorrNonLinStateEntry
            MAX-ACCESS not-accessible
            STATUS current
            DESCRIPTION
                "An entry in the txPrecorrNonLinStateTable."
            INDEX { txPrecorrNonLinStateTxIdx, txPrecorrNonLinStateExcIdx }
            ::= { txPrecorrNonLinStateTable 1 }

        
        TxPrecorrNonLinStateEntry ::=
            SEQUENCE { 
                txPrecorrNonLinStateTxIdx
                    IndexTransmitter,
                txPrecorrNonLinStateExcIdx
                    IndexAB,
                txPrecorrNonLinStateStatus
                    PrecorrectionState,
                txPrecorrNonLinStateSignalLevel
                    PrecorrectionSignalLevel,
                txPrecorrNonLinStateShoulderLeft
                    Integer32,
                txPrecorrNonLinStateShoulderRight
                    Integer32
             }

        txPrecorrNonLinStateTxIdx OBJECT-TYPE
            SYNTAX IndexTransmitter
            MAX-ACCESS not-accessible
            STATUS current
            DESCRIPTION
                "The transmitter index."
            ::= { txPrecorrNonLinStateEntry 1 }

        
        txPrecorrNonLinStateExcIdx OBJECT-TYPE
            SYNTAX IndexAB
            MAX-ACCESS not-accessible
            STATUS current
            DESCRIPTION
                "This index distinguishes the exiters.
                Necessary if you have dual drive transmitters."
            ::= { txPrecorrNonLinStateEntry 2 }

        
        txPrecorrNonLinStateStatus OBJECT-TYPE
            SYNTAX PrecorrectionState
            MAX-ACCESS read-only
            STATUS current
            DESCRIPTION
                "Nonlinear precorrection state.
                see textual convention"
            ::= { txPrecorrNonLinStateEntry 3 }

        
        txPrecorrNonLinStateSignalLevel OBJECT-TYPE
            SYNTAX PrecorrectionSignalLevel
            MAX-ACCESS read-only
            STATUS current
            DESCRIPTION
                "see textual convention"
            ::= { txPrecorrNonLinStateEntry 4 }

        
        txPrecorrNonLinStateShoulderLeft OBJECT-TYPE
            SYNTAX Integer32
            UNITS "centi Bel"
            MAX-ACCESS read-only
            STATUS current
            DESCRIPTION
                "achieved shoulder distance in the left area of signal spectrum"
            ::= { txPrecorrNonLinStateEntry 5 }

        
        txPrecorrNonLinStateShoulderRight OBJECT-TYPE
            SYNTAX Integer32
            UNITS "centi Bel"
            MAX-ACCESS read-only
            STATUS current
            DESCRIPTION
                "achieved shoulder distance in the right area of signal spectrum"
            ::= { txPrecorrNonLinStateEntry 6 }

        
        txPrecorrNonLinSetupTable OBJECT-TYPE
            SYNTAX SEQUENCE OF TxPrecorrNonLinSetupEntry
            MAX-ACCESS not-accessible
            STATUS current
            DESCRIPTION
                "Non linear precorrection settings."
            ::= { txPrecorrectionNonLinear 2 }

        
        txPrecorrNonLinSetupEntry OBJECT-TYPE
            SYNTAX TxPrecorrNonLinSetupEntry
            MAX-ACCESS not-accessible
            STATUS current
            DESCRIPTION
                "An entry in the txPrecorrNonLinSetupTable."
            AUGMENTS { txPrecorrNonLinStateEntry }
            ::= { txPrecorrNonLinSetupTable 1 }

        
        TxPrecorrNonLinSetupEntry ::=
            SEQUENCE { 
                txPrecorrNonLinSetupOpMode
                    PrecorrectionOperationMode,
                txPrecorrNonLinSetupReset
                    Trigger,
                txPrecorrNonLinSetupShoulderDistance
                    Unsigned32,
                txPrecorrNonLinSetupSignalLimit
                    Unsigned32
             }

        txPrecorrNonLinSetupOpMode OBJECT-TYPE
            SYNTAX PrecorrectionOperationMode
            MAX-ACCESS read-write
            STATUS current
            DESCRIPTION
                "see textual convention"
            ::= { txPrecorrNonLinSetupEntry 1 }

        
        txPrecorrNonLinSetupReset OBJECT-TYPE
            SYNTAX Trigger
            MAX-ACCESS read-write
            STATUS current
            DESCRIPTION
                "Reset of predistorter leads to recalculation of
                precorrection curve. Meanwhile precorrection is not active."
            ::= { txPrecorrNonLinSetupEntry 2 }

        
        txPrecorrNonLinSetupShoulderDistance OBJECT-TYPE
            SYNTAX Unsigned32 (30..45)
            UNITS "dB"
            MAX-ACCESS read-write
            STATUS current
            DESCRIPTION
                "Desired shoulder distance of the output signal."
            ::= { txPrecorrNonLinSetupEntry 3 }

        
        txPrecorrNonLinSetupSignalLimit OBJECT-TYPE
            SYNTAX Unsigned32 (60..120)
            UNITS "centi Bel"
            MAX-ACCESS read-write
            STATUS obsolete
            DESCRIPTION
                "Limits the signal on input
                of the nonlinear precorrector.
                obsolete"
            ::= { txPrecorrNonLinSetupEntry 4 }

        
        txPrecorrectionCfrTable OBJECT-TYPE
            SYNTAX SEQUENCE OF TxPrecorrectionCfrEntry
            MAX-ACCESS not-accessible
            STATUS current
            DESCRIPTION
                "crest factor reduction parameters"
            ::= { txPrecorrection 4 }

        
        txPrecorrectionCfrEntry OBJECT-TYPE
            SYNTAX TxPrecorrectionCfrEntry
            MAX-ACCESS not-accessible
            STATUS current
            DESCRIPTION
                "An entry in the txPrecorrectionCfrTable."
            INDEX { txPrecorrNotificationTxIdx, txPrecorrNotificationExcIdx }
            ::= { txPrecorrectionCfrTable 1 }

        
        TxPrecorrectionCfrEntry ::=
            SEQUENCE { 
                txPrecorrCfrEnable
                    INTEGER,
                txPrecorrCfrLevel
                    Unsigned32,
                txPrecorrCfrInbandNoise
                    Unsigned32,
                txPrecorrCfrOutbandNoise
                    Unsigned32
             }

        txPrecorrCfrEnable OBJECT-TYPE
            SYNTAX INTEGER
                {
                bypass(1),
                manual(2),
                auto(3),
                run(4)
                }
            MAX-ACCESS read-write
            STATUS current
            DESCRIPTION
                "Description."
            ::= { txPrecorrectionCfrEntry 1 }

        
        txPrecorrCfrLevel OBJECT-TYPE
            SYNTAX Unsigned32 (50..150)
            UNITS "centi Bel"
            MAX-ACCESS read-write
            STATUS current
            DESCRIPTION
                "Description."
            ::= { txPrecorrectionCfrEntry 2 }

        
        txPrecorrCfrInbandNoise OBJECT-TYPE
            SYNTAX Unsigned32 (0..100)
            UNITS "percent"
            MAX-ACCESS read-write
            STATUS current
            DESCRIPTION
                "Description."
            ::= { txPrecorrectionCfrEntry 3 }

        
        txPrecorrCfrOutbandNoise OBJECT-TYPE
            SYNTAX Unsigned32 (0..100)
            UNITS "percent"
            MAX-ACCESS read-write
            STATUS current
            DESCRIPTION
                "Description."
            ::= { txPrecorrectionCfrEntry 4 }

        
        txPrecorrSigQualTable OBJECT-TYPE
            SYNTAX SEQUENCE OF TxPrecorrSigQualEntry
            MAX-ACCESS not-accessible
            STATUS current
            DESCRIPTION
                "signal quality parameters"
            ::= { txPrecorrection 5 }

        
        txPrecorrSigQualEntry OBJECT-TYPE
            SYNTAX TxPrecorrSigQualEntry
            MAX-ACCESS not-accessible
            STATUS current
            DESCRIPTION
                "An entry in the txPrecorrSigQualTable"
            INDEX { txPrecorrSigQualTxIdx, txPrecorrSigQualExcIdx }
            ::= { txPrecorrSigQualTable 1 }

        
        TxPrecorrSigQualEntry ::=
            SEQUENCE { 
                txPrecorrSigQualTxIdx
                    IndexTransmitter,
                txPrecorrSigQualExcIdx
                    IndexAB,
                txPrecorrSigQualPapr
                    Integer32,
                txPrecorrSigQualMer
                    Integer32,
                txPrecorrSigQualMerWarnLimit
                    Integer32
             }

        txPrecorrSigQualTxIdx OBJECT-TYPE
            SYNTAX IndexTransmitter
            MAX-ACCESS not-accessible
            STATUS current
            DESCRIPTION
                "Description."
            ::= { txPrecorrSigQualEntry 1 }

        
        txPrecorrSigQualExcIdx OBJECT-TYPE
            SYNTAX IndexAB
            MAX-ACCESS not-accessible
            STATUS current
            DESCRIPTION
                "Description."
            ::= { txPrecorrSigQualEntry 2 }

        
        txPrecorrSigQualPapr OBJECT-TYPE
            SYNTAX Integer32
            UNITS "0.1 dB"
            MAX-ACCESS read-only
            STATUS current
            DESCRIPTION
                "The Peak to Average Power Ratio indicates the proportion 
                between peak and average in-band power.
                "
            ::= { txPrecorrSigQualEntry 3 }

        
        txPrecorrSigQualMer OBJECT-TYPE
            SYNTAX Integer32
            UNITS "0.1 db"
            MAX-ACCESS read-only
            STATUS current
            DESCRIPTION
                "The Modulation Error Rate indicates the signal quality. A bad MER can 
                be seen in a constellation diagram as a cloud of constellation points. A 
                high MER let look the constellation points sharper. When the MER is 
                too low a receiver can not differ between distinct constellation points an 
                produces errors. 
                "
            ::= { txPrecorrSigQualEntry 4 }

        
        txPrecorrSigQualMerWarnLimit OBJECT-TYPE
            SYNTAX Integer32
            UNITS "0.1 dB"
            MAX-ACCESS read-write
            STATUS current
            DESCRIPTION
                "Description."
            ::= { txPrecorrSigQualEntry 5 }

        
        txOutputStage OBJECT IDENTIFIER ::= { rsXx9TxObjects 9 }

        
        txOstNotificationTable OBJECT-TYPE
            SYNTAX SEQUENCE OF TxOstNotificationEntry
            MAX-ACCESS not-accessible
            STATUS current
            DESCRIPTION
                "The context information/configuration for the
                output stage status notifications."
            ::= { txOutputStage 1 }

        
        txOstNotificationEntry OBJECT-TYPE
            SYNTAX TxOstNotificationEntry
            MAX-ACCESS not-accessible
            STATUS current
            DESCRIPTION
                "An entry in the txOstNotificationTable."
            INDEX { txOstNotificationTxIdx, txOstNotificationOstIdx, txOstNotificationIdx }
            ::= { txOstNotificationTable 1 }

        
        TxOstNotificationEntry ::=
            SEQUENCE { 
                txOstNotificationTxIdx
                    IndexTransmitter,
                txOstNotificationOstIdx
                    IndexAB,
                txOstNotificationIdx
                    Unsigned32,
                txOstNotificationName
                    INTEGER,
                txOstNotificationMask
                    NotificationMask,
                txOstNotificationPriority
                    NotificationPriority,
                txOstNotificationState
                    NotificationState
             }

        txOstNotificationTxIdx OBJECT-TYPE
            SYNTAX IndexTransmitter
            MAX-ACCESS not-accessible
            STATUS current
            DESCRIPTION
                "The transmitter index."
            ::= { txOstNotificationEntry 1 }

        
        txOstNotificationOstIdx OBJECT-TYPE
            SYNTAX IndexAB
            MAX-ACCESS not-accessible
            STATUS current
            DESCRIPTION
                "This index distinguishes the output stages.
                Necessary if you have power reserve transmitters."
            ::= { txOstNotificationEntry 2 }

        
        txOstNotificationIdx OBJECT-TYPE
            SYNTAX Unsigned32 (9000)
            MAX-ACCESS not-accessible
            STATUS current
            DESCRIPTION
                "The notification number as below rsXx9TxNotifications.
                This is a helper column and therefore not-accessible."
            ::= { txOstNotificationEntry 3 }

        
        txOstNotificationName OBJECT-TYPE
            SYNTAX INTEGER { txOstSummary(9000) }
            MAX-ACCESS read-only
            STATUS current
            DESCRIPTION
                "The notification number as an enumeration.
                The enumeration correlates with the notifications under rsXx9TxNotifications."
            ::= { txOstNotificationEntry 4 }

        
        txOstNotificationMask OBJECT-TYPE
            SYNTAX NotificationMask
            MAX-ACCESS read-write
            STATUS current
            DESCRIPTION
                "See textual convention for details."
            ::= { txOstNotificationEntry 5 }

        
        txOstNotificationPriority OBJECT-TYPE
            SYNTAX NotificationPriority
            MAX-ACCESS read-write
            STATUS current
            DESCRIPTION
                "See textual convention for details."
            ::= { txOstNotificationEntry 6 }

        
        txOstNotificationState OBJECT-TYPE
            SYNTAX NotificationState
            MAX-ACCESS read-only
            STATUS current
            DESCRIPTION
                "See textual convention for details."
            ::= { txOstNotificationEntry 7 }

        
        txOstStateTable OBJECT-TYPE
            SYNTAX SEQUENCE OF TxOstStateEntry
            MAX-ACCESS not-accessible
            STATUS current
            DESCRIPTION
                "Output stage state information."
            ::= { txOutputStage 2 }

        
        txOstStateEntry OBJECT-TYPE
            SYNTAX TxOstStateEntry
            MAX-ACCESS not-accessible
            STATUS current
            DESCRIPTION
                "An entry in the txOstStateTable."
            INDEX { txOstNotificationTxIdx, txOstNotificationOstIdx }
            ::= { txOstStateTable 1 }

        
        TxOstStateEntry ::=
            SEQUENCE { 
                txOstStateRfOnHours
                    Unsigned32
             }

        txOstStateRfOnHours OBJECT-TYPE
            SYNTAX Unsigned32
            UNITS "h"
            MAX-ACCESS read-only
            STATUS current
            DESCRIPTION
                "Shows how many hours this output stage generated a
                RF signal with a level above the fault threshold."
            ::= { txOstStateEntry 3 }

        
        txOstCommandsTable OBJECT-TYPE
            SYNTAX SEQUENCE OF TxOstCommandsEntry
            MAX-ACCESS not-accessible
            STATUS current
            DESCRIPTION
                "Output stage settings."
            ::= { txOutputStage 3 }

        
        txOstCommandsEntry OBJECT-TYPE
            SYNTAX TxOstCommandsEntry
            MAX-ACCESS not-accessible
            STATUS current
            DESCRIPTION
                "An entry in the txOstCommandsTable."
            INDEX { txOstNotificationTxIdx, txOstNotificationOstIdx }
            ::= { txOstCommandsTable 1 }

        
        TxOstCommandsEntry ::=
            SEQUENCE { 
                txOstCmdPower
                    Unsigned32,
                txOstCmdDcControl
                    Integer32
             }

        txOstCmdPower OBJECT-TYPE
            SYNTAX Unsigned32 (0..1300)
            UNITS "per thousand"
            MAX-ACCESS read-write
            STATUS current
            DESCRIPTION
                "Output power of the output stage.
                About 800 o/oo correlate to the nominal power of the output stage.
                If the RF sensors are calibrated, the value adjusted here
                should determine the txOstForwardPower.
                
                The range for band II amplifiers is 0 - 1000."
            ::= { txOstCommandsEntry 1 }

        
        txOstCmdDcControl OBJECT-TYPE
            SYNTAX Integer32 (4800..11000)
            UNITS "1/100 percent"
            MAX-ACCESS read-write
            STATUS current
            DESCRIPTION
                "The range for TV amplifiers is    5000 - 11000.
                The range for band II amplifiers is 5000 - 10000.
                (DC Control for FM is only available in ConstantGain 
                mode or for FM-HD)"
            ::= { txOstCommandsEntry 3 }

        
        txAmplifier OBJECT IDENTIFIER ::= { rsXx9TxObjects 10 }

        
        txAmpNotificationTable OBJECT-TYPE
            SYNTAX SEQUENCE OF TxAmpNotificationEntry
            MAX-ACCESS not-accessible
            STATUS current
            DESCRIPTION
                "The context information/configuration for the
                amplifier status notifications."
            ::= { txAmplifier 1 }

        
        txAmpNotificationEntry OBJECT-TYPE
            SYNTAX TxAmpNotificationEntry
            MAX-ACCESS not-accessible
            STATUS current
            DESCRIPTION
                "An entry in the txAmpNotificationTable."
            INDEX { txAmpNotificationTxIdx, txAmpNotificationOstIdx, txAmpNotificationAmpIdx, txAmpNotificationIdx }
            ::= { txAmpNotificationTable 1 }

        
        TxAmpNotificationEntry ::=
            SEQUENCE { 
                txAmpNotificationTxIdx
                    IndexTransmitter,
                txAmpNotificationOstIdx
                    IndexAB,
                txAmpNotificationAmpIdx
                    Unsigned32,
                txAmpNotificationIdx
                    Unsigned32,
                txAmpNotificationName
                    INTEGER,
                txAmpNotificationMask
                    NotificationMask,
                txAmpNotificationPriority
                    NotificationPriority,
                txAmpNotificationState
                    NotificationState
             }

        txAmpNotificationTxIdx OBJECT-TYPE
            SYNTAX IndexTransmitter
            MAX-ACCESS not-accessible
            STATUS current
            DESCRIPTION
                "The transmitter index."
            ::= { txAmpNotificationEntry 1 }

        
        txAmpNotificationOstIdx OBJECT-TYPE
            SYNTAX IndexAB
            MAX-ACCESS not-accessible
            STATUS current
            DESCRIPTION
                "This index distinguishes the output stages.
                Necessary if you have power reserve transmitters."
            ::= { txAmpNotificationEntry 2 }

        
        txAmpNotificationAmpIdx OBJECT-TYPE
            SYNTAX Unsigned32 (1..72)
            MAX-ACCESS not-accessible
            STATUS current
            DESCRIPTION
                "This index distinguishes amplifiers in an output stage."
            ::= { txAmpNotificationEntry 3 }

        
        txAmpNotificationIdx OBJECT-TYPE
            SYNTAX Unsigned32 (10000..10017)
            MAX-ACCESS not-accessible
            STATUS current
            DESCRIPTION
                "The notification number as below rsXx9TxNotifications.
                This is a helper column and therefore not-accessible."
            ::= { txAmpNotificationEntry 4 }

        
        txAmpNotificationName OBJECT-TYPE
            SYNTAX INTEGER
                {
                txAmpSummary(10000),
                txAmpRfPowerFail(10001),
                txAmpReflection(10002),
                txAmpSupplyFail(10003),
                txAmpRfInFail(10004),
                txAmpMute(10005),
                txAmpTemperatureFail(10006),
                txAmpTransistorFail(10007),
                txAmpRegulationFail(10008),
                txAmpAcFail(10009),
                txAmpDcFail(10010),
                txAmpDriverFail(10011),
                txAmpLink(10012),
                txAmpBiasFail(10013),
                txAmpInitFail(10014),
                txAmpAbsorberFail(10015),
                txAmpOn(10016),
                txAmpBlocking(10017)
                }
            MAX-ACCESS read-only
            STATUS current
            DESCRIPTION
                "The notification number as an enumeration.
                The enumeration correlates with the notifications under rsXx9TxNotifications."
            ::= { txAmpNotificationEntry 5 }

        
        txAmpNotificationMask OBJECT-TYPE
            SYNTAX NotificationMask
            MAX-ACCESS read-write
            STATUS current
            DESCRIPTION
                "See textual convention for details."
            ::= { txAmpNotificationEntry 6 }

        
        txAmpNotificationPriority OBJECT-TYPE
            SYNTAX NotificationPriority
            MAX-ACCESS read-write
            STATUS current
            DESCRIPTION
                "See textual convention for details."
            ::= { txAmpNotificationEntry 7 }

        
        txAmpNotificationState OBJECT-TYPE
            SYNTAX NotificationState
            MAX-ACCESS read-only
            STATUS current
            DESCRIPTION
                "See textual convention for details."
            ::= { txAmpNotificationEntry 8 }

        
        txAmplifierStateTable OBJECT-TYPE
            SYNTAX SEQUENCE OF TxAmplifierStateEntry
            MAX-ACCESS not-accessible
            STATUS current
            DESCRIPTION
                "General amplifier state information."
            ::= { txAmplifier 2 }

        
        txAmplifierStateEntry OBJECT-TYPE
            SYNTAX TxAmplifierStateEntry
            MAX-ACCESS not-accessible
            STATUS current
            DESCRIPTION
                "An entry in the txAmplifierStateTable."
            INDEX { txAmpNotificationTxIdx, txAmpNotificationOstIdx, txAmpNotificationAmpIdx }
            ::= { txAmplifierStateTable 1 }

        
        TxAmplifierStateEntry ::=
            SEQUENCE { 
                txAmpStI1A
                    Unsigned32,
                txAmpStI2A
                    Unsigned32,
                txAmpStI3A
                    Unsigned32,
                txAmpStI1B
                    Unsigned32,
                txAmpStI2B
                    Unsigned32,
                txAmpStI3B
                    Unsigned32,
                txAmpStIDrv
                    Unsigned32,
                txAmpStIPre
                    Unsigned32,
                txAmpStPwrA
                    Unsigned32,
                txAmpStPwrB
                    Unsigned32,
                txAmpStPwrOut
                    Unsigned32,
                txAmpStReflOut
                    Unsigned32,
                txAmpStVRefPwr
                    Unsigned32,
                txAmpStVReg
                    Unsigned32,
                txAmpStVPlusMon
                    Unsigned32,
                txAmpStIDc
                    Unsigned32,
                txAmpStVPreMon
                    Unsigned32,
                txAmpStVAuxIn
                    Unsigned32,
                txAmpStV12Mon
                    Unsigned32,
                txAmpStV5Acb
                    Unsigned32,
                txAmpStV3V5
                    Unsigned32,
                txAmpStTemperature
                    Integer32,
                txAmpStRfMonitor
                    Integer32
             }

        txAmpStI1A OBJECT-TYPE
            SYNTAX Unsigned32
            UNITS "1/100 A"
            MAX-ACCESS read-only
            STATUS current
            DESCRIPTION
                "Current flowing through transistors V14 and V15 (PHU901)
                and V500 (PMU901) in transistor block A."
            ::= { txAmplifierStateEntry 1 }

        
        txAmpStI2A OBJECT-TYPE
            SYNTAX Unsigned32
            UNITS "1/100 A"
            MAX-ACCESS read-only
            STATUS current
            DESCRIPTION
                "Current flowing through transistors V16 and V17 (PHU901)
                and V1500 (PMU901) in transistor block A."
            ::= { txAmplifierStateEntry 2 }

        
        txAmpStI3A OBJECT-TYPE
            SYNTAX Unsigned32
            UNITS "1/100 A"
            MAX-ACCESS read-only
            STATUS current
            DESCRIPTION
                "Current flowing through transistors V18 and V19 (PHU901)
                and V2500 (PMU901) in transistor block A.
                
                only for PHU901, PHU902 and PMU901"
            ::= { txAmplifierStateEntry 3 }

        
        txAmpStI1B OBJECT-TYPE
            SYNTAX Unsigned32
            UNITS "1/100 A"
            MAX-ACCESS read-only
            STATUS current
            DESCRIPTION
                "Current flowing through transistors V24 and V25 (PHU901)
                and V600 (PMU901) in transistor block B."
            ::= { txAmplifierStateEntry 4 }

        
        txAmpStI2B OBJECT-TYPE
            SYNTAX Unsigned32
            UNITS "1/100 A"
            MAX-ACCESS read-only
            STATUS current
            DESCRIPTION
                "Current flowing through transistors V26 and V27 (PHU901)
                and V1600 (PMU901) in transistor block B."
            ::= { txAmplifierStateEntry 5 }

        
        txAmpStI3B OBJECT-TYPE
            SYNTAX Unsigned32
            UNITS "1/100 A"
            MAX-ACCESS read-only
            STATUS current
            DESCRIPTION
                "Current flowing through transistors V28 and V29 (PHU901)
                and V2600 (PMU901) in transistor block B.
                
                only for PHU901, PHU902 and PMU901"
            ::= { txAmplifierStateEntry 6 }

        
        txAmpStIDrv OBJECT-TYPE
            SYNTAX Unsigned32
            UNITS "1/100 A"
            MAX-ACCESS read-only
            STATUS current
            DESCRIPTION
                "Current flowing through the transistors of the driver module. "
            ::= { txAmplifierStateEntry 7 }

        
        txAmpStIPre OBJECT-TYPE
            SYNTAX Unsigned32
            UNITS "1/100 A"
            MAX-ACCESS read-only
            STATUS current
            DESCRIPTION
                "Current flowing through transistors of the preamplifier module."
            ::= { txAmplifierStateEntry 8 }

        
        txAmpStPwrA OBJECT-TYPE
            SYNTAX Unsigned32
            UNITS "1/100 V"
            MAX-ACCESS read-only
            STATUS current
            DESCRIPTION
                "Measured voltage of the RF detector
                in transistor block A.
                
                not for PMU901"
            ::= { txAmplifierStateEntry 9 }

        
        txAmpStPwrB OBJECT-TYPE
            SYNTAX Unsigned32
            UNITS "1/100 V"
            MAX-ACCESS read-only
            STATUS current
            DESCRIPTION
                "Measured voltage of the RF detector
                in transistor block B.
                
                not for PMU901"
            ::= { txAmplifierStateEntry 10 }

        
        txAmpStPwrOut OBJECT-TYPE
            SYNTAX Unsigned32
            UNITS "1/100 V"
            MAX-ACCESS read-only
            STATUS current
            DESCRIPTION
                "Measured voltage of the RF detector
                at the output of the amplifier."
            ::= { txAmplifierStateEntry 11 }

        
        txAmpStReflOut OBJECT-TYPE
            SYNTAX Unsigned32
            UNITS "1/100 V"
            MAX-ACCESS read-only
            STATUS current
            DESCRIPTION
                "Measured voltage of the RF detector
                for the reflected power."
            ::= { txAmplifierStateEntry 12 }

        
        txAmpStVRefPwr OBJECT-TYPE
            SYNTAX Unsigned32
            UNITS "1/100 V"
            MAX-ACCESS read-only
            STATUS current
            DESCRIPTION
                "Nominal value predefined by theTCE900 for internal 
                control of the output power. 
                - With DVB and ATV signals, a value of 4 V roughly 
                  corresponds to the nominal power of the amplifier. 
                - With ATV, a value of 4.18 V roughly corresponds to 
                  the nominal power of the amplifier. 
                - With ATSC, a value of 4.56 volts roughly corresponds 
                  to the nominal power of the amplifier."
            ::= { txAmplifierStateEntry 13 }

        
        txAmpStVReg OBJECT-TYPE
            SYNTAX Unsigned32
            UNITS "1/10 V"
            MAX-ACCESS read-only
            STATUS obsolete
            DESCRIPTION
                "Adjustment value for internal control of the output power."
            ::= { txAmplifierStateEntry 14 }

        
        txAmpStVPlusMon OBJECT-TYPE
            SYNTAX Unsigned32
            UNITS "1/10 V"
            MAX-ACCESS read-only
            STATUS current
            DESCRIPTION
                "Displays the voltage supplied to the transistor blocks by 
                the power supply unit. With PMU9, the displayed voltage 
                should be approx. 44 V. With PHU9, the displayed 
                voltage varies during adjustment between approx. 35 V 
                and approx. 50 V. If the displayed voltage is 0 V, either 
                the power supply unit is faulty or the amplifier has not 
                been switched on.
                "
            ::= { txAmplifierStateEntry 15 }

        
        txAmpStIDc OBJECT-TYPE
            SYNTAX Unsigned32
            UNITS "1/10 A"
            MAX-ACCESS read-only
            STATUS current
            DESCRIPTION
                "Total current which is supplied by the internal power supply units. 
                If the displayed current is 0 A, the amplifier has not been switched 
                on by the TCE900 or one of the following faults 
                has occurred: 
                - RF In Fail 
                - Temperature Fail 
                - DC Fail
                "
            ::= { txAmplifierStateEntry 16 }

        
        txAmpStVPreMon OBJECT-TYPE
            SYNTAX Unsigned32
            UNITS "1/10 V"
            MAX-ACCESS read-only
            STATUS current
            DESCRIPTION
                "Supply voltage of the preamplifier. In the ON state, it 
                is approx. 20 V and is generated on the preamplifier 
                board. The displayed voltage is 0 V if the amplifier 
                has been switched off by the TCE900. 
                If no voltage is indicated in the ON state, the automatic 
                circuit breakers of the energy distribution and the 
                self-engaging contacts on the rear panel of the amplifier 
                should be checked first of all. If no fault can be found in 
                the energy feed, the amplifier must be replaced.
                
                not for PMV901"
            ::= { txAmplifierStateEntry 17 }

        
        txAmpStVAuxIn OBJECT-TYPE
            SYNTAX Unsigned32
            UNITS "1/10 V"
            MAX-ACCESS read-only
            STATUS current
            DESCRIPTION
                "Supply voltage of the amplifier control board. This auxiliary 
                voltage is generated directly by the power supply unit and 
                is fed to the amplifier control board via the preamplifier 
                board. This voltage should be present at the amplifier control 
                board even if the amplifier has been switched off by the 
                TCE900. If no voltage is displayed, the automatic circuit 
                breakers of the power distribution as well as the self-engaging 
                contacts on the rear panel of the amplifier should be checked 
                first of all. If no fault can be found in the energy feed, 
                the amplifier must be replaced.
                "
            ::= { txAmplifierStateEntry 18 }

        
        txAmpStV12Mon OBJECT-TYPE
            SYNTAX Unsigned32
            UNITS "1/10 V"
            MAX-ACCESS read-only
            STATUS current
            DESCRIPTION
                "12 V auxiliary voltage which is generated on the preamplifier 
                board from the 20 V supply voltage (txAmpStVPreMon). If the 
                amplifier has not been switched on by the TCE900, the voltage 
                is approx. 8 V.
                "
            ::= { txAmplifierStateEntry 19 }

        
        txAmpStV5Acb OBJECT-TYPE
            SYNTAX Unsigned32
            UNITS "1/100 V"
            MAX-ACCESS read-only
            STATUS current
            DESCRIPTION
                "5 V auxiliary voltage which is generated on the amplifier control 
                board from the auxiliary voltage (txAmpStVAuxIn) of the power 
                supply unit. If no voltage is indicated, the automatic circuit 
                breakers of the energy distribution and also the self-engaging 
                contacts on the rear panel of the amplifier should be checked 
                first of all. If no fault can be found in the energy feed, the amplifier 
                must be replaced.
                "
            ::= { txAmplifierStateEntry 20 }

        
        txAmpStV3V5 OBJECT-TYPE
            SYNTAX Unsigned32
            UNITS "1/100 V"
            MAX-ACCESS read-only
            STATUS current
            DESCRIPTION
                "3.5 V auxiliary voltage which is generated on the amplifier 
                control board from the auxiliary voltage (txAmpStVAuxIn) of 
                the power supply unit. If no voltage is indicated, the automatic 
                circuit breakers of the energy distribution and also the 
                self-engaging contacts on the rear panel of the amplifier 
                should be checked first of all. If no fault can be found in the 
                energy feed, the amplifier must be replaced. 
                "
            ::= { txAmplifierStateEntry 21 }

        
        txAmpStTemperature OBJECT-TYPE
            SYNTAX Integer32
            UNITS "1/10 degree celsius"
            MAX-ACCESS read-only
            STATUS current
            DESCRIPTION
                "Amplifier temperature;
                usually a few degrees higher than the coolant temperature.
                If the difference is greater than 15 deg C, either the stop valves 
                are closed or the coolant flow is too low."
            ::= { txAmplifierStateEntry 22 }

        
        txAmpStRfMonitor OBJECT-TYPE
            SYNTAX Integer32
            UNITS "milli Bel"
            MAX-ACCESS read-only
            STATUS current
            DESCRIPTION
                "Coupling attenuation of the 'RF monitor' test point
                at 650 MHz."
            ::= { txAmplifierStateEntry 23 }

        
        txAmplifierPmxTable OBJECT-TYPE
            SYNTAX SEQUENCE OF TxAmplifierPmxEntry
            MAX-ACCESS not-accessible
            STATUS current
            DESCRIPTION
                "Specific parameters for PMU and PMV amplifiers."
            ::= { txAmplifier 3 }

        
        txAmplifierPmxEntry OBJECT-TYPE
            SYNTAX TxAmplifierPmxEntry
            MAX-ACCESS not-accessible
            STATUS current
            DESCRIPTION
                "An entry in the txAmplifierPmxTable."
            INDEX { txAmpNotificationTxIdx, txAmpNotificationOstIdx, txAmpNotificationAmpIdx }
            ::= { txAmplifierPmxTable 1 }

        
        TxAmplifierPmxEntry ::=
            SEQUENCE { 
                txPmxFanFail
                    NotificationState,
                txPmxAirFilterFail
                    NotificationState,
                txPmxFrequencyFail
                    NotificationState,
                txPmxFreqID
                    Unsigned32,
                txPmxInletAirTemperature
                    Integer32,
                txPmxOutletAirTemperature
                    Integer32,
                txPmxvRefPowerMax
                    Unsigned32,
                txPmxFreqIDString
                    SnmpAdminString,
                txPmxDohertyActive
                    DohertyActive
             }

        txPmxFanFail OBJECT-TYPE
            SYNTAX NotificationState
            MAX-ACCESS read-only
            STATUS current
            DESCRIPTION
                "Indicates whether the fans used to dissipate heat from the
                amplifier module are functioning.
                
                off(2)   - fans are functioning correctly
                warning(4) "
            ::= { txAmplifierPmxEntry 1 }

        
        txPmxAirFilterFail OBJECT-TYPE
            SYNTAX NotificationState
            MAX-ACCESS read-only
            STATUS obsolete
            DESCRIPTION
                "off(2)
                warning(4) - High difference between inlet and outlet air temperature.
                             Air filter probably clogged."
            ::= { txAmplifierPmxEntry 2 }

        
        txPmxFrequencyFail OBJECT-TYPE
            SYNTAX NotificationState
            MAX-ACCESS read-only
            STATUS current
            DESCRIPTION
                "This fault occurs if the tunit (tuning unit) used in the amplifier 
                is not suitable for the RF of the exciter. The tunit is a plug-in 
                module and is on the top side of the amplifier. Please check 
                that the used tunit is suitable for the frequency which is set in 
                the Output menu of the exciter, and whether it has been 
                installed in the amplifier in the 'Doherty' or 'Broadband' 
                position corresponding to the setting in the 'Basic Config' 
                menu in the GUI.
                
                off(2)   - 
                fault(3) - The tuning unit in the amplifier is not suitable
                           for the RF of the exciter.
                
                for PMU901 only"
            ::= { txAmplifierPmxEntry 3 }

        
        txPmxFreqID OBJECT-TYPE
            SYNTAX Unsigned32
            MAX-ACCESS read-only
            STATUS obsolete
            DESCRIPTION
                "ID that the tuning unit in amplifier must have
                for the intended frequency.
                Obsoleted - see txPmxFreqIDString for a replacement. "
            ::= { txAmplifierPmxEntry 4 }

        
        txPmxInletAirTemperature OBJECT-TYPE
            SYNTAX Integer32
            UNITS "1/10 degree celsius"
            MAX-ACCESS read-only
            STATUS current
            DESCRIPTION
                "Inlet air temperature of the amplifier module. 
                It should always be in the range +1 degree C to +45 
                degrees celsius."
            ::= { txAmplifierPmxEntry 5 }

        
        txPmxOutletAirTemperature OBJECT-TYPE
            SYNTAX Integer32
            UNITS "1/10 degree celsius"
            MAX-ACCESS read-only
            STATUS current
            DESCRIPTION
                "Outlet air temperature of the amplifier module."
            ::= { txAmplifierPmxEntry 6 }

        
        txPmxvRefPowerMax OBJECT-TYPE
            SYNTAX Unsigned32
            UNITS "mV"
            MAX-ACCESS read-only
            STATUS obsolete
            DESCRIPTION
                "maximal admissible reference voltage"
            ::= { txAmplifierPmxEntry 7 }

        
        txPmxFreqIDString OBJECT-TYPE
            SYNTAX SnmpAdminString
            MAX-ACCESS read-only
            STATUS current
            DESCRIPTION
                "ID of the frequency range in Doherty mode
                "
            ::= { txAmplifierPmxEntry 8 }

        
        txPmxDohertyActive OBJECT-TYPE
            SYNTAX DohertyActive
            MAX-ACCESS read-only
            STATUS current
            DESCRIPTION
                "Indicates whether the Doherty mode of the amplifier is active or not.
                
                for PMV901 only
                "
            ::= { txAmplifierPmxEntry 9 }

        
        txAmplifierPhr901Table OBJECT-TYPE
            SYNTAX SEQUENCE OF TxAmplifierPhr901Entry
            MAX-ACCESS not-accessible
            STATUS current
            DESCRIPTION
                "specific PHR901 parameters."
            ::= { txAmplifier 4 }

        
        txAmplifierPhr901Entry OBJECT-TYPE
            SYNTAX TxAmplifierPhr901Entry
            MAX-ACCESS not-accessible
            STATUS current
            DESCRIPTION
                "An entry in the txAmplifierPhr901Table."
            INDEX { txAmpNotificationTxIdx, txAmpNotificationOstIdx, txAmpNotificationAmpIdx }
            ::= { txAmplifierPhr901Table 1 }

        
        TxAmplifierPhr901Entry ::=
            SEQUENCE { 
                txPhr901PwrA
                    Unsigned32,
                txPhr901PwrB
                    Unsigned32,
                txPhr901PwrOutAv
                    Unsigned32,
                txPhr901ReflOutAv
                    Unsigned32,
                txPhr901PwrAbs
                    Unsigned32,
                txPhr901PwrIn
                    Unsigned32,
                txPhr901PwrDrv
                    Unsigned32,
                txPhr901I12
                    Unsigned32,
                txPhr901I34
                    Unsigned32,
                txPhr901I56
                    Unsigned32,
                txPhr901I78
                    Unsigned32
             }

        txPhr901PwrA OBJECT-TYPE
            SYNTAX Unsigned32
            UNITS "mW"
            MAX-ACCESS read-only
            STATUS obsolete
            DESCRIPTION
                "The measured power of the RF detector in transistor block A."
            ::= { txAmplifierPhr901Entry 1 }

        
        txPhr901PwrB OBJECT-TYPE
            SYNTAX Unsigned32
            UNITS "mW"
            MAX-ACCESS read-only
            STATUS obsolete
            DESCRIPTION
                "The measured power of the RF detector in transistor block B."
            ::= { txAmplifierPhr901Entry 2 }

        
        txPhr901PwrOutAv OBJECT-TYPE
            SYNTAX Unsigned32
            UNITS "mW"
            MAX-ACCESS read-only
            STATUS obsolete
            DESCRIPTION
                "The measured forward power at the output of the amplifier."
            ::= { txAmplifierPhr901Entry 3 }

        
        txPhr901ReflOutAv OBJECT-TYPE
            SYNTAX Unsigned32
            UNITS "mW"
            MAX-ACCESS read-only
            STATUS obsolete
            DESCRIPTION
                "The measured reflected power at the output of  the amplifier."
            ::= { txAmplifierPhr901Entry 4 }

        
        txPhr901PwrAbs OBJECT-TYPE
            SYNTAX Unsigned32
            UNITS "mW"
            MAX-ACCESS read-only
            STATUS obsolete
            DESCRIPTION
                "The measured power on the final absorber of the amplifier."
            ::= { txAmplifierPhr901Entry 5 }

        
        txPhr901PwrIn OBJECT-TYPE
            SYNTAX Unsigned32
            UNITS "1/100 V"
            MAX-ACCESS read-only
            STATUS current
            DESCRIPTION
                "The measured power at the input of the amplifier."
            ::= { txAmplifierPhr901Entry 6 }

        
        txPhr901PwrDrv OBJECT-TYPE
            SYNTAX Unsigned32
            UNITS "1/100 V"
            MAX-ACCESS read-only
            STATUS current
            DESCRIPTION
                "The measured power of the driver stage of the amplifier."
            ::= { txAmplifierPhr901Entry 7 }

        
        txPhr901I12 OBJECT-TYPE
            SYNTAX Unsigned32
            UNITS "1/100 A"
            MAX-ACCESS read-only
            STATUS current
            DESCRIPTION
                "The sum of measured currents of transistors T101 and T102."
            ::= { txAmplifierPhr901Entry 8 }

        
        txPhr901I34 OBJECT-TYPE
            SYNTAX Unsigned32
            UNITS "1/100 A"
            MAX-ACCESS read-only
            STATUS current
            DESCRIPTION
                "The sum of measured currents of transistors T103 and T104."
            ::= { txAmplifierPhr901Entry 9 }

        
        txPhr901I56 OBJECT-TYPE
            SYNTAX Unsigned32
            UNITS "1/100 A"
            MAX-ACCESS read-only
            STATUS current
            DESCRIPTION
                "The sum of measured currents of transistors T105 and T106."
            ::= { txAmplifierPhr901Entry 10 }

        
        txPhr901I78 OBJECT-TYPE
            SYNTAX Unsigned32
            UNITS "1/100 A"
            MAX-ACCESS read-only
            STATUS current
            DESCRIPTION
                "The sum of measured currents of transistors T107 and T108."
            ::= { txAmplifierPhr901Entry 11 }

        
        txAmplifierPhxTable OBJECT-TYPE
            SYNTAX SEQUENCE OF TxAmplifierPhxEntry
            MAX-ACCESS not-accessible
            STATUS current
            DESCRIPTION
                "Specific parameters for PHU and PHV amplifiers."
            ::= { txAmplifier 5 }

        
        txAmplifierPhxEntry OBJECT-TYPE
            SYNTAX TxAmplifierPhxEntry
            MAX-ACCESS not-accessible
            STATUS current
            DESCRIPTION
                "An entry in the txAmplifierPhxTable."
            INDEX { txAmpNotificationTxIdx, txAmpNotificationOstIdx, txAmpNotificationAmpIdx }
            ::= { txAmplifierPhxTable 1 }

        
        TxAmplifierPhxEntry ::=
            SEQUENCE { 
                txPhxFreqID
                    Unsigned32,
                txPhxFreqIDString
                    SnmpAdminString,
                txPhxDohertyActive
                    DohertyActive
             }

        txPhxFreqID OBJECT-TYPE
            SYNTAX Unsigned32
            MAX-ACCESS read-only
            STATUS obsolete
            DESCRIPTION
                "ID that the tuning unit in amplifier must have
                for the intended frequency.
                Obsoleted - see txPhxFreqIDString for a replacement."
            ::= { txAmplifierPhxEntry 1 }

        
        txPhxFreqIDString OBJECT-TYPE
            SYNTAX SnmpAdminString
            MAX-ACCESS read-only
            STATUS current
            DESCRIPTION
                "ID of the frequency range in Doherty mode
                
                for PHU902 and PHV902 only"
            ::= { txAmplifierPhxEntry 2 }

        
        txPhxDohertyActive OBJECT-TYPE
            SYNTAX DohertyActive
            MAX-ACCESS read-only
            STATUS current
            DESCRIPTION
                "Indicates whether the Doherty mode of the amplifier is active or not.
                
                for PHU902 and PHV902 only"
            ::= { txAmplifierPhxEntry 3 }

        
        txAmplifierTlxTable OBJECT-TYPE
            SYNTAX SEQUENCE OF TxAmplifierTlxEntry
            MAX-ACCESS not-accessible
            STATUS current
            DESCRIPTION
                "Specific parameters for TLx amplifiers."
            ::= { txAmplifier 6 }

        
        txAmplifierTlxEntry OBJECT-TYPE
            SYNTAX TxAmplifierTlxEntry
            MAX-ACCESS not-accessible
            STATUS current
            DESCRIPTION
                "An entry in the txAmplifierTlxTable,"
            INDEX { txAmpNotificationTxIdx, txAmpNotificationOstIdx, txAmpNotificationAmpIdx }
            ::= { txAmplifierTlxTable 1 }

        
        TxAmplifierTlxEntry ::=
            SEQUENCE { 
                txAmpTlxFanFail
                    NotificationState,
                txAmpTlxV12Mon
                    Unsigned32,
                txAmpTlxSupplyFail
                    NotificationState
             }

        txAmpTlxFanFail OBJECT-TYPE
            SYNTAX NotificationState
            MAX-ACCESS read-only
            STATUS current
            DESCRIPTION
                "Description."
            ::= { txAmplifierTlxEntry 1 }

        
        txAmpTlxV12Mon OBJECT-TYPE
            SYNTAX Unsigned32
            UNITS "1/100V"
            MAX-ACCESS read-only
            STATUS current
            DESCRIPTION
                "Description."
            ::= { txAmplifierTlxEntry 2 }

        
        txAmpTlxSupplyFail OBJECT-TYPE
            SYNTAX NotificationState
            MAX-ACCESS read-only
            STATUS current
            DESCRIPTION
                "Description."
            ::= { txAmplifierTlxEntry 3 }

        
        txSwitchlessCombiner OBJECT IDENTIFIER ::= { rsXx9TxObjects 11 }

        
        txSwiCoNotificationTable OBJECT-TYPE
            SYNTAX SEQUENCE OF TxSwiCoNotificationEntry
            MAX-ACCESS not-accessible
            STATUS current
            DESCRIPTION
                "The context information/configuration for the
                Switchless Combiner status notifications.
                Only available if Switchless Combiner is configured. "
            ::= { txSwitchlessCombiner 1 }

        
        txSwiCoNotificationEntry OBJECT-TYPE
            SYNTAX TxSwiCoNotificationEntry
            MAX-ACCESS not-accessible
            STATUS current
            DESCRIPTION
                "An entry in the txSwiCoNotificationTable."
            INDEX { txSwiCoNotificationTxIdx, txSwiCoNotificationSwiCoIdx, txSwiCoNotificationIdx }
            ::= { txSwiCoNotificationTable 1 }

        
        TxSwiCoNotificationEntry ::=
            SEQUENCE { 
                txSwiCoNotificationTxIdx
                    IndexTransmitter,
                txSwiCoNotificationSwiCoIdx
                    Unsigned32,
                txSwiCoNotificationIdx
                    Unsigned32,
                txSwiCoNotificationName
                    INTEGER,
                txSwiCoNotificationMask
                    NotificationMask,
                txSwiCoNotificationPriority
                    NotificationPriority,
                txSwiCoNotificationState
                    NotificationState
             }

        txSwiCoNotificationTxIdx OBJECT-TYPE
            SYNTAX IndexTransmitter
            MAX-ACCESS not-accessible
            STATUS current
            DESCRIPTION
                "The transmitter index."
            ::= { txSwiCoNotificationEntry 1 }

        
        txSwiCoNotificationSwiCoIdx OBJECT-TYPE
            SYNTAX Unsigned32 (1)
            MAX-ACCESS not-accessible
            STATUS current
            DESCRIPTION
                "This index distinguishes Switchless Combiners."
            ::= { txSwiCoNotificationEntry 2 }

        
        txSwiCoNotificationIdx OBJECT-TYPE
            SYNTAX Unsigned32 (11000..11008)
            MAX-ACCESS not-accessible
            STATUS current
            DESCRIPTION
                "The notification number as below rsXx9TxNotifications.
                This is a helper column and therefore not-accessible."
            ::= { txSwiCoNotificationEntry 3 }

        
        txSwiCoNotificationName OBJECT-TYPE
            SYNTAX INTEGER
                {
                txSwiCoSummary(11000),
                txSwiCoHwLink(11001),
                txSwiCoHwWarn(11002),
                txSwiCoHwFault(11003),
                txSwiCoHwLocal(11004),
                txSwiCoRcbFail(11005),
                txSwiCoRfProbeFail(11006),
                txSwiCoRegulationSummary(11007)
                }
            MAX-ACCESS read-only
            STATUS current
            DESCRIPTION
                "The notification number as an enumeration.
                The enumeration correlates with the notifications under rsXx9TxNotifications."
            ::= { txSwiCoNotificationEntry 4 }

        
        txSwiCoNotificationMask OBJECT-TYPE
            SYNTAX NotificationMask
            MAX-ACCESS read-write
            STATUS current
            DESCRIPTION
                "See textual convention for details."
            ::= { txSwiCoNotificationEntry 5 }

        
        txSwiCoNotificationPriority OBJECT-TYPE
            SYNTAX NotificationPriority
            MAX-ACCESS read-write
            STATUS current
            DESCRIPTION
                "See textual convention for details."
            ::= { txSwiCoNotificationEntry 6 }

        
        txSwiCoNotificationState OBJECT-TYPE
            SYNTAX NotificationState
            MAX-ACCESS read-only
            STATUS current
            DESCRIPTION
                "See textual convention for details."
            ::= { txSwiCoNotificationEntry 7 }

        
        txSwiCoStateTable OBJECT-TYPE
            SYNTAX SEQUENCE OF TxSwiCoStateEntry
            MAX-ACCESS not-accessible
            STATUS current
            DESCRIPTION
                "General Switchless Combiner state information.
                Only available is Switchless Combiner is configured. "
            ::= { txSwitchlessCombiner 2 }

        
        txSwiCoStateEntry OBJECT-TYPE
            SYNTAX TxSwiCoStateEntry
            MAX-ACCESS not-accessible
            STATUS current
            DESCRIPTION
                "An entry in the txSwiCoStateTable."
            INDEX { txSwiCoNotificationTxIdx, txSwiCoNotificationSwiCoIdx }
            ::= { txSwiCoStateTable 1 }

        
        TxSwiCoStateEntry ::=
            SEQUENCE { 
                txSwiCoStRegulationState
                    INTEGER,
                txSwiCoStCalibrationState
                    INTEGER,
                txSwiCoStPosGraded
                    Unsigned32,
                txSwiCoStPosDegree
                    Integer32,
                txSwiCoStPosPermil
                    Unsigned32
             }

        txSwiCoStRegulationState OBJECT-TYPE
            SYNTAX INTEGER
                {
                stablePosition(1),
                increasingPhaseAngle(2),
                decreasingPhaseAngle(3)
                }
            MAX-ACCESS read-only
            STATUS current
            DESCRIPTION
                "Indicates whether the control is currently working. 
                Hold: The phase angle is constant. 
                Phase decreasing/Phase increasing: The phase angle is currently being changed.
                "
            ::= { txSwiCoStateEntry 1 }

        
        txSwiCoStCalibrationState OBJECT-TYPE
            SYNTAX INTEGER
                {
                calibrated(1),
                notCalibrated(2)
                }
            MAX-ACCESS read-only
            STATUS current
            DESCRIPTION
                "Indicates whether the switchless combiner has been calibrated for the 
                current transmitter frequency. 
                OK: The switchless combiner is calibrated. 
                Warning: The switchless combiner has not yet been calibrated.
                "
            ::= { txSwiCoStateEntry 2 }

        
        txSwiCoStPosGraded OBJECT-TYPE
            SYNTAX Unsigned32 (0..5)
            MAX-ACCESS read-only
            STATUS current
            DESCRIPTION
                "Shows the position of Switchless Combiner in these steps:
                0: < 0deg
                1: 0deg
                2: between 0deg and 90 deg (2 and 4 racks) or 110deg (3 racks)
                3: 90deg (2 and 4 racks) or 110deg (3 racks)
                4: between 90deg (2 and 4 racks) or 110deg (3 racks) and 180deg
                5: > 180deg"
            ::= { txSwiCoStateEntry 3 }

        
        txSwiCoStPosDegree OBJECT-TYPE
            SYNTAX Integer32 (-1..500)
            MAX-ACCESS read-only
            STATUS current
            DESCRIPTION
                "Indicates the current effective phase angle between the two inputs. 
                If the coupling is symmetric, the phase angle is 90 degrees. If the 
                switchless combiner has not yet been calibrated for the current 
                transmitter frequency, the display shows a %.
                "
            ::= { txSwiCoStateEntry 4 }

        
        txSwiCoStPosPermil OBJECT-TYPE
            SYNTAX Unsigned32 (0..1000)
            MAX-ACCESS read-only
            STATUS current
            DESCRIPTION
                "Indicates the current effective phase angle between the two inputs. If the coupling 
                is symmetric, the phase angle is 90 degrees. If the switchless combiner has not 
                yet been calibrated for the current transmitter frequency, the display shows a %.
                "
            ::= { txSwiCoStateEntry 5 }

        
        txSwiCoCommandsTable OBJECT-TYPE
            SYNTAX SEQUENCE OF TxSwiCoCommandsEntry
            MAX-ACCESS not-accessible
            STATUS current
            DESCRIPTION
                "Switchless Cominer settings. 
                Only available is Switchless Combiner is configured. "
            ::= { txSwitchlessCombiner 3 }

        
        txSwiCoCommandsEntry OBJECT-TYPE
            SYNTAX TxSwiCoCommandsEntry
            MAX-ACCESS not-accessible
            STATUS current
            DESCRIPTION
                "An entry in the txSwiCoCommandsTable."
            INDEX { txSwiCoNotificationTxIdx, txSwiCoNotificationSwiCoIdx }
            ::= { txSwiCoCommandsTable 1 }

        
        TxSwiCoCommandsEntry ::=
            SEQUENCE { 
                txSwiCoCmdAutomatic
                    INTEGER,
                txSwiCoCmdManualPosition
                    INTEGER,
                txSwiCoCmdActivationThreshold
                    Unsigned32
             }

        txSwiCoCmdAutomatic OBJECT-TYPE
            SYNTAX INTEGER
                {
                manual(1),
                automatic(2)
                }
            MAX-ACCESS read-write
            STATUS current
            DESCRIPTION
                "Switches the automatic power control of the rack combiner on and off.
                "
            ::= { txSwiCoCommandsEntry 1 }

        
        txSwiCoCmdManualPosition OBJECT-TYPE
            SYNTAX INTEGER
                {
                undefinedPosition(1),
                position1(2),
                position2(3),
                position1and2(4)
                }
            MAX-ACCESS read-write
            STATUS current
            DESCRIPTION
                "Indicates which input was switched to the antenna when automatic ^
                is switched off. The setting can be changed here.
                "
            ::= { txSwiCoCommandsEntry 2 }

        
        txSwiCoCmdActivationThreshold OBJECT-TYPE
            SYNTAX Unsigned32 (0..600)
            UNITS "0.01-dB"
            MAX-ACCESS read-write
            STATUS current
            DESCRIPTION
                "If the output power is below the nominal power minus this activation threshold value, the Switchless Combiner Automatic will react."
            ::= { txSwiCoCommandsEntry 3 }

        
        txPresets OBJECT IDENTIFIER ::= { rsXx9TxObjects 12 }

        
        txPresetCommandsTable OBJECT-TYPE
            SYNTAX SEQUENCE OF TxPresetCommandsEntry
            MAX-ACCESS not-accessible
            STATUS current
            DESCRIPTION
                "Description."
            ::= { txPresets 2 }

        
        txPresetCommandsEntry OBJECT-TYPE
            SYNTAX TxPresetCommandsEntry
            MAX-ACCESS not-accessible
            STATUS current
            DESCRIPTION
                "Description."
            INDEX { txPresetCmdTxIdx }
            ::= { txPresetCommandsTable 1 }

        
        TxPresetCommandsEntry ::=
            SEQUENCE { 
                txPresetCmdTxIdx
                    IndexTransmitter,
                txPresetCmdLoadPreset1
                    Trigger,
                txPresetCmdLoadPreset2
                    Trigger,
                txPresetCmdLoadPreset3
                    Trigger,
                txPresetCmdLoadPreset4
                    Trigger,
                txPresetCmdSavePreset1
                    Trigger,
                txPresetCmdSavePreset2
                    Trigger,
                txPresetCmdSavePreset3
                    Trigger,
                txPresetCmdSavePreset4
                    Trigger
             }

        txPresetCmdTxIdx OBJECT-TYPE
            SYNTAX IndexTransmitter
            MAX-ACCESS not-accessible
            STATUS current
            DESCRIPTION
                "Description."
            ::= { txPresetCommandsEntry 1 }

        
        txPresetCmdLoadPreset1 OBJECT-TYPE
            SYNTAX Trigger
            MAX-ACCESS read-write
            STATUS current
            DESCRIPTION
                "Activates one of up to four previously saved sets of program and feed 
                setting values. If a name is assigned to a preset, this name appears 
                on the button. 'Load Preset' is only available for used memory locations.
                "
            ::= { txPresetCommandsEntry 2 }

        
        txPresetCmdLoadPreset2 OBJECT-TYPE
            SYNTAX Trigger
            MAX-ACCESS read-write
            STATUS current
            DESCRIPTION
                "Activates one of up to four previously saved sets of program and feed 
                setting values. If a name is assigned to a preset, this name appears 
                on the button. 'Load Preset' is only available for used memory locations.
                "
            ::= { txPresetCommandsEntry 3 }

        
        txPresetCmdLoadPreset3 OBJECT-TYPE
            SYNTAX Trigger
            MAX-ACCESS read-write
            STATUS current
            DESCRIPTION
                "Activates one of up to four previously saved sets of program and feed 
                setting values. If a name is assigned to a preset, this name appears 
                on the button. 'Load Preset' is only available for used memory locations.
                "
            ::= { txPresetCommandsEntry 4 }

        
        txPresetCmdLoadPreset4 OBJECT-TYPE
            SYNTAX Trigger
            MAX-ACCESS read-write
            STATUS current
            DESCRIPTION
                "Activates one of up to four previously saved sets of program and feed 
                setting values. If a name is assigned to a preset, this name appears 
                on the button. 'Load Preset' is only available for used memory locations.
                "
            ::= { txPresetCommandsEntry 5 }

        
        txPresetCmdSavePreset1 OBJECT-TYPE
            SYNTAX Trigger
            MAX-ACCESS read-write
            STATUS current
            DESCRIPTION
                "Saves all currently active program and feed settings to one of four memory 
                locations. Previously saved settings are overwritten. If a name is assigned 
                to a preset, this name appears on the button. 'Save Preset' is only available 
                if all components of the transmitter are operating correctly.
                "
            ::= { txPresetCommandsEntry 6 }

        
        txPresetCmdSavePreset2 OBJECT-TYPE
            SYNTAX Trigger
            MAX-ACCESS read-write
            STATUS current
            DESCRIPTION
                "Saves all currently active program and feed settings to one of four memory 
                locations. Previously saved settings are overwritten. If a name is assigned 
                to a preset, this name appears on the button. 'Save Preset' is only available 
                if all components of the transmitter are operating correctly.
                "
            ::= { txPresetCommandsEntry 7 }

        
        txPresetCmdSavePreset3 OBJECT-TYPE
            SYNTAX Trigger
            MAX-ACCESS read-write
            STATUS current
            DESCRIPTION
                "Saves all currently active program and feed settings to one of four memory 
                locations. Previously saved settings are overwritten. If a name is assigned 
                to a preset, this name appears on the button. 'Save Preset' is only available 
                if all components of the transmitter are operating correctly.
                "
            ::= { txPresetCommandsEntry 8 }

        
        txPresetCmdSavePreset4 OBJECT-TYPE
            SYNTAX Trigger
            MAX-ACCESS read-write
            STATUS current
            DESCRIPTION
                "Saves all currently active program and feed settings to one of four memory 
                locations. Previously saved settings are overwritten. If a name is assigned 
                to a preset, this name appears on the button. 'Save Preset' is only available 
                if all components of the transmitter are operating correctly.
                "
            ::= { txPresetCommandsEntry 9 }

        
        txPresetStatusTable OBJECT-TYPE
            SYNTAX SEQUENCE OF TxPresetStatusEntry
            MAX-ACCESS not-accessible
            STATUS current
            DESCRIPTION
                "Description."
            ::= { txPresets 3 }

        
        txPresetStatusEntry OBJECT-TYPE
            SYNTAX TxPresetStatusEntry
            MAX-ACCESS not-accessible
            STATUS current
            DESCRIPTION
                "Description."
            INDEX { txPresetCmdTxIdx }
            ::= { txPresetStatusTable 1 }

        
        TxPresetStatusEntry ::=
            SEQUENCE { 
                txPresetStActivePreset
                    INTEGER,
                txPresetStProgramSettings
                    INTEGER
             }

        txPresetStActivePreset OBJECT-TYPE
            SYNTAX INTEGER
                {
                notActive(0),
                preset1(1),
                preset2(2),
                preset3(3),
                preset4(4)
                }
            MAX-ACCESS read-only
            STATUS current
            DESCRIPTION
                "Indicates which settings are currently active. If a preset has not yet been 
                loaded, 'Not Active' is displayed."
            ::= { txPresetStatusEntry 1 }

        
        txPresetStProgramSettings OBJECT-TYPE
            SYNTAX INTEGER
                {
                undefined(1),
                notSaved(2),
                saved(3)
                }
            MAX-ACCESS read-only
            STATUS current
            DESCRIPTION
                "Shows a warning if, after a preset is loaded, the currently active settings have 
                been changed but not yet saved again in a preset. In this case, data will be 
                lost if the preset is switched over to a different preset. If all memory locations 
                are empty, 'Presets not Used' appears. "
            ::= { txPresetStatusEntry 2 }

        
        txRfSensors OBJECT IDENTIFIER ::= { rsXx9TxObjects 13 }

        
        txRfSensorsNotificationTable OBJECT-TYPE
            SYNTAX SEQUENCE OF TxRfSensorsNotificationEntry
            MAX-ACCESS not-accessible
            STATUS current
            DESCRIPTION
                "The context information/configuration for the
                Switchless Combiner status notifications."
            ::= { txRfSensors 1 }

        
        txRfSensorsNotificationEntry OBJECT-TYPE
            SYNTAX TxRfSensorsNotificationEntry
            MAX-ACCESS not-accessible
            STATUS current
            DESCRIPTION
                "An entry in the txRfSensorsNotificationTable."
            INDEX { txRfSensorsNotificationTxIdx, txRfSensorsNotificationSensorIdx, txRfSensorsNotificationIdx }
            ::= { txRfSensorsNotificationTable 1 }

        
        TxRfSensorsNotificationEntry ::=
            SEQUENCE { 
                txRfSensorsNotificationTxIdx
                    IndexTransmitter,
                txRfSensorsNotificationSensorIdx
                    Unsigned32,
                txRfSensorsNotificationIdx
                    Unsigned32,
                txRfSensorsNotificationName
                    INTEGER,
                txRfSensorsNotificationMask
                    NotificationMask,
                txRfSensorsNotificationPriority
                    NotificationPriority,
                txRfSensorsNotificationState
                    NotificationState
             }

        txRfSensorsNotificationTxIdx OBJECT-TYPE
            SYNTAX IndexTransmitter
            MAX-ACCESS not-accessible
            STATUS current
            DESCRIPTION
                "The transmitter index."
            ::= { txRfSensorsNotificationEntry 1 }

        
        txRfSensorsNotificationSensorIdx OBJECT-TYPE
            SYNTAX Unsigned32 (1..6)
            MAX-ACCESS not-accessible
            STATUS current
            DESCRIPTION
                "This index distinguishes Rf sensors. 
                
                Rf sensor 1 of a Tx is the Tx's antenna sensor. 
                Rf sensor 2 of a Tx is the Tx's lower antenna sensor (in half antenna configuration).
                Rf sensor 3 of a Tx is the Tx's upper antenna sensor (in half antenna configuration).
                
                "
            ::= { txRfSensorsNotificationEntry 2 }

        
        txRfSensorsNotificationIdx OBJECT-TYPE
            SYNTAX Unsigned32 (12000..12001)
            MAX-ACCESS not-accessible
            STATUS current
            DESCRIPTION
                "The notification number as below rsXx9TxNotifications.
                This is a helper column and therefore not-accessible."
            ::= { txRfSensorsNotificationEntry 3 }

        
        txRfSensorsNotificationName OBJECT-TYPE
            SYNTAX INTEGER
                {
                txRfSensorLinkStatus(12000),
                txRfSensorCalibrated(12001)
                }
            MAX-ACCESS read-only
            STATUS current
            DESCRIPTION
                "The notification number as an enumeration.
                The enumeration correlates with the notifications under rsXx9TxNotifications."
            ::= { txRfSensorsNotificationEntry 4 }

        
        txRfSensorsNotificationMask OBJECT-TYPE
            SYNTAX NotificationMask
            MAX-ACCESS read-write
            STATUS current
            DESCRIPTION
                "See textual convention for details."
            ::= { txRfSensorsNotificationEntry 5 }

        
        txRfSensorsNotificationPriority OBJECT-TYPE
            SYNTAX NotificationPriority
            MAX-ACCESS read-write
            STATUS current
            DESCRIPTION
                "See textual convention for details."
            ::= { txRfSensorsNotificationEntry 6 }

        
        txRfSensorsNotificationState OBJECT-TYPE
            SYNTAX NotificationState
            MAX-ACCESS read-only
            STATUS current
            DESCRIPTION
                "See textual convention for details."
            ::= { txRfSensorsNotificationEntry 7 }

        
        txRfSensorsTable OBJECT-TYPE
            SYNTAX SEQUENCE OF TxRfSensorsEntry
            MAX-ACCESS not-accessible
            STATUS current
            DESCRIPTION
                "Transmitter Antenna Rf threshold configuration and status."
            ::= { txRfSensors 2 }

        
        txRfSensorsEntry OBJECT-TYPE
            SYNTAX TxRfSensorsEntry
            MAX-ACCESS not-accessible
            STATUS current
            DESCRIPTION
                "An entry in the txRfSensorsTable."
            INDEX { txRfSensorsNotificationTxIdx, txRfSensorsNotificationSensorIdx }
            ::= { txRfSensorsTable 1 }

        
        TxRfSensorsEntry ::=
            SEQUENCE { 
                txRfLimitForwardFail
                    Integer32,
                txRfLimitForwardWarn
                    Integer32,
                txRfLimitReflectedFail
                    Integer32,
                txRfLimitReflectedWarn
                    Integer32,
                txRfLimitForwardPercentFailUpper
                    Unsigned32,
                txRfLimitForwardPercentFailLower
                    Integer32,
                txRfLimitForwardPercentWarnUpper
                    Unsigned32,
                txRfLimitForwardPercentWarnLower
                    Integer32,
                txRfLimitReflectedVswrFail
                    Integer32,
                txRfLimitReflectedVswrWarn
                    Integer32,
                txRfCmdForwardFailTimeout
                    Unsigned32,
                txRfStForwardPercent
                    Unsigned32,
                txRfStReflectedVswr
                    Integer32,
                txRfStForward
                    Unsigned32,
                txRfStReflected
                    Unsigned32,
                txRfIdentify
                    Trigger,
                txRfCalibrate
                    Trigger,
                txRfUncalibrate
                    Trigger,
                txRfLimitForwardAddUpperFail
                    Integer32,
                txRfLimitForwardAddUpperWarn
                    Integer32
             }

        txRfLimitForwardFail OBJECT-TYPE
            SYNTAX Integer32 (-4000..0)
            UNITS "0.01 dB"
            MAX-ACCESS read-write
            STATUS current
            DESCRIPTION
                "Description."
            ::= { txRfSensorsEntry 1 }

        
        txRfLimitForwardWarn OBJECT-TYPE
            SYNTAX Integer32 (-4000..0)
            UNITS "0.01 dB"
            MAX-ACCESS read-write
            STATUS current
            DESCRIPTION
                "Description."
            ::= { txRfSensorsEntry 2 }

        
        txRfLimitReflectedFail OBJECT-TYPE
            SYNTAX Integer32 (-1700..-600)
            UNITS "0.01 dB"
            MAX-ACCESS read-write
            STATUS current
            DESCRIPTION
                "Description."
            ::= { txRfSensorsEntry 3 }

        
        txRfLimitReflectedWarn OBJECT-TYPE
            SYNTAX Integer32 (-2800..-1700)
            UNITS "0.01 dB"
            MAX-ACCESS read-write
            STATUS current
            DESCRIPTION
                "Description."
            ::= { txRfSensorsEntry 4 }

        
        txRfLimitForwardPercentFailUpper OBJECT-TYPE
            SYNTAX Unsigned32 (1..1000)
            UNITS "0.1 %"
            MAX-ACCESS read-write
            STATUS current
            DESCRIPTION
                "Description.
                
                only valid for antennaRfProbe"
            ::= { txRfSensorsEntry 5 }

        
        txRfLimitForwardPercentFailLower OBJECT-TYPE
            SYNTAX Integer32 (-990..1)
            UNITS "0.1 %"
            MAX-ACCESS read-write
            STATUS current
            DESCRIPTION
                "Description.
                
                only valid for antennaRfProbe"
            ::= { txRfSensorsEntry 6 }

        
        txRfLimitForwardPercentWarnUpper OBJECT-TYPE
            SYNTAX Unsigned32 (1..100)
            UNITS "0.1 %"
            MAX-ACCESS read-write
            STATUS current
            DESCRIPTION
                "Description.
                
                only valid for antennaRfProbe"
            ::= { txRfSensorsEntry 7 }

        
        txRfLimitForwardPercentWarnLower OBJECT-TYPE
            SYNTAX Integer32 (-990..1)
            UNITS "0.1 %"
            MAX-ACCESS read-write
            STATUS current
            DESCRIPTION
                "Description.
                
                only valid for antennaRfProbe"
            ::= { txRfSensorsEntry 8 }

        
        txRfLimitReflectedVswrFail OBJECT-TYPE
            SYNTAX Integer32 (1330..3000)
            UNITS "0.001 VSWR"
            MAX-ACCESS read-write
            STATUS current
            DESCRIPTION
                "Description.
                
                only valid for antennaRfProbe"
            ::= { txRfSensorsEntry 9 }

        
        txRfLimitReflectedVswrWarn OBJECT-TYPE
            SYNTAX Integer32 (1080..1330)
            UNITS "0.001 VSWR"
            MAX-ACCESS read-write
            STATUS current
            DESCRIPTION
                "Description.
                
                only valid for antennaRfProbe"
            ::= { txRfSensorsEntry 10 }

        
        txRfCmdForwardFailTimeout OBJECT-TYPE
            SYNTAX Unsigned32 (0..60)
            UNITS "s"
            MAX-ACCESS read-write
            STATUS current
            DESCRIPTION
                "Description."
            ::= { txRfSensorsEntry 11 }

        
        txRfStForwardPercent OBJECT-TYPE
            SYNTAX Unsigned32 (0..2000)
            UNITS "0.1 %"
            MAX-ACCESS read-only
            STATUS current
            DESCRIPTION
                "Description.
                
                only valid for antennaRfProbe"
            ::= { txRfSensorsEntry 12 }

        
        txRfStReflectedVswr OBJECT-TYPE
            SYNTAX Integer32 (0 | 100..1000)
            UNITS "0.001 VSWR"
            MAX-ACCESS read-only
            STATUS current
            DESCRIPTION
                "Description.
                
                A value of 0 means: invalid
                only valid for antennaRfProbe"
            ::= { txRfSensorsEntry 13 }

        
        txRfStForward OBJECT-TYPE
            SYNTAX Unsigned32
            UNITS "milli W"
            MAX-ACCESS read-only
            STATUS current
            DESCRIPTION
                "Description."
            ::= { txRfSensorsEntry 14 }

        
        txRfStReflected OBJECT-TYPE
            SYNTAX Unsigned32
            UNITS "milli W"
            MAX-ACCESS read-only
            STATUS current
            DESCRIPTION
                "Description."
            ::= { txRfSensorsEntry 15 }

        
        txRfIdentify OBJECT-TYPE
            SYNTAX Trigger
            MAX-ACCESS read-write
            STATUS current
            DESCRIPTION
                "Identifies the power sensor to which a calibrated power meter has to be connected.
                When this button is pushed, a green LED on the power sensor will start flashing.
                Looking into the rack from the reverse, the flashing LED will mark the position of 
                the power sensor. The LED automatically stops blinking after thirty seconds.
                "
            ::= { txRfSensorsEntry 16 }

        
        txRfCalibrate OBJECT-TYPE
            SYNTAX Trigger
            MAX-ACCESS read-write
            STATUS current
            DESCRIPTION
                "Description."
            ::= { txRfSensorsEntry 17 }

        
        txRfUncalibrate OBJECT-TYPE
            SYNTAX Trigger
            MAX-ACCESS read-write
            STATUS current
            DESCRIPTION
                "Description."
            ::= { txRfSensorsEntry 18 }

        
        txRfLimitForwardAddUpperFail OBJECT-TYPE
            SYNTAX Integer32 (-1000..1000)
            UNITS "0.01 dB"
            MAX-ACCESS read-write
            STATUS current
            DESCRIPTION
                "Description.
                
                only valid for additional probes."
            ::= { txRfSensorsEntry 19 }

        
        txRfLimitForwardAddUpperWarn OBJECT-TYPE
            SYNTAX Integer32 (-2000..1000)
            UNITS "0.01 dB"
            MAX-ACCESS read-write
            STATUS current
            DESCRIPTION
                "Description.
                
                only valid for additional probes."
            ::= { txRfSensorsEntry 20 }

        
        rsXx9TxConformance OBJECT IDENTIFIER ::= { rsXx9Tx 2 }

        
        rsXx9TxCompliances OBJECT IDENTIFIER ::= { rsXx9TxConformance 1 }

        
        txBasicCompliance MODULE-COMPLIANCE
            STATUS current
            DESCRIPTION 
                "The compliance statement for XX9000 TV transmitters."
            MODULE -- this module
                MANDATORY-GROUPS { txObjsExciter, txObjsSFN, txObjsInputInterfaces, txObjsInputAutomatic, txNotifySFN, 
                    txNotifyInputInterfaces, txObjsPrecorrection, txNotifyInputAutomatic, txObjsOutputStage, txNotifyAmplifier, 
                    txObjsAmplifier, txNotifyOutputStage, txNotifyPrecorrection, txNotifyFrequencyRegulation, txObjsFrequencyRegulation, 
                    txObjsNonBand2, txObjsNonFM, txNotifyExciter, txObjsTransmitter, txNotifyTransmitter
                     }
                GROUP txObjsExciterAutomatic
                    DESCRIPTION 
                        "only for DualDrive/BackupDrive transmitters"
                GROUP txNotifyExciterAutomatic
                    DESCRIPTION 
                        "only for DualDrive/BackupDrive transmitters"
                GROUP txObjsDualDrive
                    DESCRIPTION 
                        "only for DualDrive transmitters"
                GROUP txObjsSFN1
                    DESCRIPTION 
                        "for DVB-T, ISDB-T, DTMB only"
                GROUP txObjsPMx
                    DESCRIPTION 
                        "for PMU or PMV amplifiers only"
                GROUP txObjsSFN2
                    DESCRIPTION 
                        "SFN objects not for ISDB-T."
                GROUP txObjsInputTsFeed
                    DESCRIPTION 
                        "not for ATV, DAB, FM"
                GROUP txNotifyInputTsFeed
                    DESCRIPTION 
                        "not for ATV, DAB, FM"
                GROUP txObjsPHx902
                    DESCRIPTION 
                        "for PHU902 and PHV902 only"
                GROUP txObjsPMU901
                    DESCRIPTION 
                        "for PMU901 only"
                GROUP txObjsPMV901
                    DESCRIPTION 
                        "for PMV901 only"
            ::= { rsXx9TxCompliances 1 }

        
        txBand2Compliance MODULE-COMPLIANCE
            STATUS current
            DESCRIPTION 
                "The compliance statement for XX9000 band II transmitters."
            MODULE -- this module
                MANDATORY-GROUPS { txObjsExciter, txObjsInputAutomatic, txNotifyInputAutomatic, txObjsOutputStage, txNotifyAmplifier, 
                    txObjsAmplifier, txNotifyOutputStage, txObjsPHR901, txNotifyFrequencyRegulation, txObjsFrequencyRegulation, 
                    txNotifyExciter, txObjsTransmitter, txNotifyTransmitter }
                GROUP txObjsExciterAutomatic
                    DESCRIPTION 
                        "only for DualDrive/BackupDrive transmitters"
                GROUP txNotifyExciterAutomatic
                    DESCRIPTION 
                        "only for DualDrive/BackupDrive transmitters"
                GROUP txObjsDualDrive
                    DESCRIPTION 
                        "only for DualDrive transmitters"
                OBJECT txOstCmdPower
                    SYNTAX Unsigned32 (0..1000)
                    DESCRIPTION 
                        "different range for PMR amplifiers"
                GROUP txObjsNonFM
                    DESCRIPTION 
                        "not for modulation mode FM"
                OBJECT txExcCmdFrequency
                    SYNTAX Unsigned32 (87500000..108000000)
                    DESCRIPTION 
                        "Value range for band2 transmitters."
            ::= { rsXx9TxCompliances 2 }

        
        rsXx9TxGroups OBJECT IDENTIFIER ::= { rsXx9TxConformance 2 }

        
        txObjsTransmitter OBJECT-GROUP
            OBJECTS { txTransmitterNotificationName, txTransmitterNotificationMask, txTransmitterNotificationPriority, txTransmitterNotificationState, txTransCmdReset, 
                txTransCmdOperationMode, txTransCmdNominalPower, txTransStForwardPower, txTransStReflectedPower, txTransStModulationMode, 
                txTransStPrimaryModMode, txTransCmdPrgOnAfterSumFault, txTransCmdReflectionCheck, txTransCmdWarnOnDohertyMismatch, txTransStSecondaryModMode, 
                txTransCmdChangeModulation }
            STATUS current
            DESCRIPTION 
                "General transmitter objects group."
            ::= { rsXx9TxGroups 1 }

        
        txObjsExciter OBJECT-GROUP
            OBJECTS { txExcCmdModulationMode, txExcCmdOutputAttenuation, txExcStOperationOn, txExcCmdLoopControl, txExcCmdOperationMode, 
                txExcCmdFrequency, txExciterNotificationName, txExciterNotificationMask, txExciterNotificationPriority, txExciterNotificationState
                 }
            STATUS current
            DESCRIPTION 
                "Exciter objects group."
            ::= { rsXx9TxGroups 2 }

        
        txObjsInputInterfaces OBJECT-GROUP
            OBJECTS { txIpFeedStreamProtocol, txIpFeedStreamPort, txIpFeedStreamAddress, txIpFeedStreamAddressType, txIpFeedStreamingMode, 
                txIpFeedConnector, txInpGsMultiplexName, txInpGsInputSource, txInpMonitorOut, txIpFeedPacketsOutOfRange, 
                txIpFeedPacketsReordered, txIpFeedPacketsDuplicate, txIpFeedPacketsFixed, txIpFeedPacketsMissing, txIpFeedPacketsTotal, 
                txIpFeedLinkStatus, txIpFeedDatarate, txInpIfNotificationName, txInpIfNotificationMask, txInpIfNotificationPriority, 
                txInpIfNotificationState }
            STATUS current
            DESCRIPTION 
                "Input interface objects group.
                in case of a missing physical input connector or 
                missing option key, changes to objects in this 
                group might be ignored. "
            ::= { rsXx9TxGroups 3 }

        
        txObjsInputTsFeed OBJECT-GROUP
            OBJECTS { txTsFeedBruttoDataRate, txTsFeedNettoDataRate, txTsFeedPacketLength, txTsFeedType }
            STATUS current
            DESCRIPTION 
                "Input TS feed objects group.
                in case of a missing physical input connector or 
                missing option key, changes to objects in this 
                group might be ignored. "
            ::= { rsXx9TxGroups 4 }

        
        txObjsInputAutomatic OBJECT-GROUP
            OBJECTS { txInpAutoNotificationName, txInpAutoNotificationMask, txInpAutoNotificationPriority, txInpAutoNotificationState, txInpAutoOperationMode, 
                txInpAutoGuardTimeToReserve, txInpAutoIfReseveFails, txInpAutoForceExciterChangeover, txInpAutoActiveInput, txInpAutoDelayInput1To2, 
                txInpAutoGuardTimeBack, txInpAutoDirection }
            STATUS current
            DESCRIPTION 
                "Input automatic objects group."
            ::= { rsXx9TxGroups 5 }

        
        txObjsFrequencyRegulation OBJECT-GROUP
            OBJECTS { txFrqRegSetupSource, txFrqRegSetupControllerMode, txFrqRegSetupRefFailPermissionTime, txFrqRegSetupMuteOnFail, txFrqRegSetupManualOcxoAdjust, 
                txFrqRegSetupMonitor, txFrqRegNotificationName, txFrqRegStateController, txFrqRegStateCurrentSource, txFrqRegNotificationState, 
                txFrqRegStateCurrentControllerMode, txFrqRegNotificationPriority, txFrqRegNotificationMask }
            STATUS current
            DESCRIPTION 
                "Frequency regulation objects group."
            ::= { rsXx9TxGroups 6 }

        
        txObjsSFN OBJECT-GROUP
            OBJECTS { txSfnNotificationName, txSfnNotificationMask, txSfnNotificationPriority, txSfnNotificationState, txSfnStateInternalPpsValid, 
                txSfnStateProcessingTime, txSfnStateDynamicDelay, txSfnStateTotalDelay, txSfnSetupSource, txSfnSetupMaxDeviation, 
                txSfnStatePPS, txSfnStateSFN, txSfnSetupStaticDelay, txSfnStateTransmissionInTime }
            STATUS current
            DESCRIPTION 
                "SFN objects group."
            ::= { rsXx9TxGroups 7 }

        
        txObjsPrecorrection OBJECT-GROUP
            OBJECTS { txPrecorrNotificationName, txPrecorrNotificationMask, txPrecorrNotificationPriority, txPrecorrNotificationState }
            STATUS current
            DESCRIPTION 
                "Precorrection objects group.
                also see txObjsLinPrecorrection, txObjsNonLinPrecorrection and txObjsPrecorrectionCfr objects groups. "
            ::= { rsXx9TxGroups 8 }

        
        txObjsOutputStage OBJECT-GROUP
            OBJECTS { txOstNotificationName, txOstNotificationMask, txOstNotificationPriority, txOstNotificationState, txOstStateRfOnHours, 
                txOstCmdPower }
            STATUS current
            DESCRIPTION 
                "Output stage objects group."
            ::= { rsXx9TxGroups 9 }

        
        txObjsAmplifier OBJECT-GROUP
            OBJECTS { txAmpNotificationName, txAmpNotificationMask, txAmpNotificationPriority, txAmpNotificationState, txAmpStIDrv, 
                txAmpStIPre, txAmpStVRefPwr, txAmpStVPlusMon, txAmpStIDc, txAmpStVPreMon, 
                txAmpStVAuxIn, txAmpStV12Mon, txAmpStV5Acb, txAmpStV3V5, txAmpStTemperature, 
                txAmpStRfMonitor, txAmpStPwrA, txAmpStPwrB, txAmpStPwrOut, txAmpStReflOut
                 }
            STATUS current
            DESCRIPTION 
                "Common high-power (PHx) and medium-power (PMx) 
                amplifier objects group.
                "
            ::= { rsXx9TxGroups 10 }

        
        txObjsSwitchlessCombiner OBJECT-GROUP
            OBJECTS { txSwiCoNotificationName, txSwiCoNotificationMask, txSwiCoNotificationPriority, txSwiCoNotificationState, txSwiCoStPosGraded, 
                txSwiCoStPosDegree, txSwiCoStRegulationState, txSwiCoCmdAutomatic, txSwiCoCmdManualPosition, txSwiCoCmdActivationThreshold, 
                txSwiCoStCalibrationState, txSwiCoStPosPermil }
            STATUS current
            DESCRIPTION 
                "Common switchless combiner objects group."
            ::= { rsXx9TxGroups 11 }

        
        txObjsActiveReserve OBJECT-GROUP
            OBJECTS { txArExcAutomaticOperationMode, txArExcAutomaticMode, txArExcAutomaticGuardTime, txArPreselectExcA, txArPreselectExcB, 
                txArExcPreselected, txArExcSelected, txArOstAutomaticOperationMode, txArOstAutomaticMode, txArOstAutomaticGuardTime, 
                txArOstPreselected, txArOstSelected, txArPreselectOstAtoDlOstBtoAnt, txArPreselectOstAtoAntOstBtoDl, txArPreselectOstAOstBtoDl, 
                txArPreselectOstAOstBtoAnt }
            STATUS current
            DESCRIPTION 
                "Common active reserve objects group."
            ::= { rsXx9TxGroups 12 }

        
        txObjsInputSatFeed OBJECT-GROUP
            OBJECTS { txSatTunerTransponderFreq, txSatTunerSignalType, txSatTunerSymbolRate, txSatTunerModulation, txSatTunerCoderate, 
                txSatTunerSignalStandard, txSatTunerRxPower, txSatTunerMeasuredTsDatarate, txSatTunerBitErrorRate, txSatTunerCarrierNoiseRatio, 
                txSatTunerTsSymbolRate, txSatLnbPolarization, txSatLnbFreqLowBand, txSatLnbFreqHighBand, txSatLnbVoltage, 
                txSatCamInserted, txSatCamStatus, txSatCamManufacturerName, txSatCamModuleName, txSatCamTsInput, 
                txSatCamTsOutput, txSatCamConfigurationMode, txSatCamBissMode, txSatCamBissInjectedId, txSatCamBissEncryptedSession, 
                txSatCamBissClearSession, txSatFeedInputServiceName, txSatFeedInputServiceID, txSatFeedInputServiceType, txSatFeedInputServiceElementaryStreams, 
                txSatFeedInputServiceDecryption, txSatFeedInputServiceEncrypted, txSatFeedInputServiceDecryptionState, txSatIpOutMulticastAddrType, txSatGeneralAsiOutput, 
                txSatLnb22kHzSignal, txSatLnbFreqCBand, txSatLnbBand, txSatTunerIntermediateFreq, txSatFeedDecryptionServiceID, 
                txSatBtsNullPacketLcPid, txSatBtsNullPacketLbPid, txSatBtsNullPacketLaPid, txSatBtsPliTablePid, txSatTunerLinkMargin, 
                txSatMultiStreamUsedStreamId, txSatMultiStreamStatus, txSatCamScExpirationDate, txSatCamScManufacturerName, txSatCamScInserted, 
                txSatLnbDriftWarnLimit, txSatTunerCarrierNoiseWarnLimit, txSatTunerLinkMarginFaultLimit, txSatTunerLinkMarginWarnLimit, txSatCamReset, 
                txSatCamResetMode, txSatPlsActive, txSatPlsSelect, txSatCodeLoop, txSatPlsCode3, 
                txSatPlsCode2, txSatLnbDrift, txSatTunerCarrierNoiseFaultLimit, txSatFeedInputServicePmtPid, txSatStreamExpectedTsId, 
                txSatStreamCurrentTsId, txSatLnbFreqCBandLower32, txSatLnbFreqCBandUpper32, txSatLnbFreqHighBandLower32, txSatLnbFreqHighBandUpper32, 
                txSatLnbFreqLowBandLower32, txSatLnbFreqLowBandUpper32, txSatTunerTransponderFreqLower32, txSatTunerTransponderFreqUpper32, txSatIpOutMulticastAddr, 
                txSatIpOutPort, txSatIpOutFecRow, txSatIpOutFecCol, txSatIpOutLocalIpAddrType, txSatIpOutLocalIpAddr, 
                txSatIpOutLocalNetmaskAddrType, txSatIpOutLocalNetmask, txSatIpOutMacAddr, txSatPlScrambling, txSatPlsCode
                 }
            STATUS current
            DESCRIPTION 
                "Common SAT receiver objects group."
            ::= { rsXx9TxGroups 13 }

        
        txObjsPreset OBJECT-GROUP
            OBJECTS { txPresetStProgramSettings, txPresetStActivePreset, txPresetCmdSavePreset4, txPresetCmdSavePreset3, txPresetCmdSavePreset2, 
                txPresetCmdSavePreset1, txPresetCmdLoadPreset4, txPresetCmdLoadPreset3, txPresetCmdLoadPreset2, txPresetCmdLoadPreset1
                 }
            STATUS current
            DESCRIPTION 
                "Preset related objects."
            ::= { rsXx9TxGroups 14 }

        
        txObjsRfSensors OBJECT-GROUP
            OBJECTS { txRfLimitForwardFail, txRfLimitForwardWarn, txRfLimitReflectedFail, txRfLimitReflectedWarn, txRfLimitForwardPercentFailUpper, 
                txRfLimitForwardPercentFailLower, txRfLimitForwardPercentWarnUpper, txRfLimitForwardPercentWarnLower, txRfLimitReflectedVswrFail, txRfLimitReflectedVswrWarn, 
                txRfCmdForwardFailTimeout, txRfStForwardPercent, txRfStReflected, txRfStForward, txRfUncalibrate, 
                txRfCalibrate, txRfIdentify, txRfStReflectedVswr, txRfSensorsNotificationName, txRfSensorsNotificationMask, 
                txRfSensorsNotificationPriority, txRfSensorsNotificationState, txRfLimitForwardAddUpperFail, txRfLimitForwardAddUpperWarn }
            STATUS current
            DESCRIPTION 
                "RF Sensor objects"
            ::= { rsXx9TxGroups 15 }

        
        txNotifyTransmitter NOTIFICATION-GROUP
            NOTIFICATIONS { txSummary, txRfSensorSummary, txLocal, txRF, txReflection
                 }
            STATUS current
            DESCRIPTION 
                "General transmitter notifications group."
            ::= { rsXx9TxGroups 101 }

        
        txNotifyExciter NOTIFICATION-GROUP
            NOTIFICATIONS { txExciterSummary, txExciterLoop, txExciterMute, txExciterOutputConnect, txExciterRfState
                 }
            STATUS current
            DESCRIPTION 
                "Exciter notifications group."
            ::= { rsXx9TxGroups 102 }

        
        txNotifyInputInterfaces NOTIFICATION-GROUP
            NOTIFICATIONS { txInpIfLogDatarateBufferOverflow, txInpIfLogDatarateBufferUnderrun, txInpIfIpState, txInpIfLogState, txInpIfLogInfoPacket, 
                txInpIfLogPacketLength, txInpIfIpInfoPacket, txInpIfIpPacketLength }
            STATUS current
            DESCRIPTION 
                "Input interface notifications group."
            ::= { rsXx9TxGroups 103 }

        
        txNotifyInputTsFeed NOTIFICATION-GROUP
            NOTIFICATIONS { txInpIfTsState, txInpIfTsInfoPacket, txInpIfTsPacketLength }
            STATUS current
            DESCRIPTION 
                "Input TS feed notifications group."
            ::= { rsXx9TxGroups 104 }

        
        txNotifyInputAutomatic NOTIFICATION-GROUP
            NOTIFICATIONS { txInpAuto1Active, txInpAutoState }
            STATUS current
            DESCRIPTION 
                "Input automatic notifications group."
            ::= { rsXx9TxGroups 105 }

        
        txNotifyFrequencyRegulation NOTIFICATION-GROUP
            NOTIFICATIONS { txFrqRegSummary, txFrqRegCurrentSource, txFrqRegSourceExtRef, txFrqRegSourceExtPPS, txFrqRegSourceIntGPS
                 }
            STATUS current
            DESCRIPTION 
                "Frequency regulation notifications group."
            ::= { rsXx9TxGroups 106 }

        
        txNotifySFN NOTIFICATION-GROUP
            NOTIFICATIONS { txSfnSummary }
            STATUS current
            DESCRIPTION 
                "SFN notifications group."
            ::= { rsXx9TxGroups 107 }

        
        txNotifyPrecorrection NOTIFICATION-GROUP
            NOTIFICATIONS { txPrecorrLinSummary, txPrecorrNonLinSummary }
            STATUS current
            DESCRIPTION 
                "Precorrection notifications group.
                obsoleted.
                check txNotifyLinPrecorrection and txNotifyNonLinPrecorrection notifications groups instead. "
            ::= { rsXx9TxGroups 108 }

        
        txNotifyOutputStage NOTIFICATION-GROUP
            NOTIFICATIONS { txOstSummary }
            STATUS current
            DESCRIPTION 
                "Output stage notifications group."
            ::= { rsXx9TxGroups 109 }

        
        txNotifyAmplifier NOTIFICATION-GROUP
            NOTIFICATIONS { txAmpSummary, txAmpRfPowerFail, txAmpReflection, txAmpSupplyFail, txAmpRfInFail, 
                txAmpMute, txAmpTemperatureFail, txAmpTransistorFail, txAmpRegulationFail, txAmpAcFail, 
                txAmpDcFail, txAmpLink, txAmpBiasFail, txAmpInitFail, txAmpAbsorberFail, 
                txAmpOn, txAmpBlocking }
            STATUS current
            DESCRIPTION 
                "High-power (PHx) and medium-power (PMx) 
                amplifier notifications group."
            ::= { rsXx9TxGroups 110 }

        
        txNotifySwitchlessCombiner NOTIFICATION-GROUP
            NOTIFICATIONS { txSwiCoSummary, txSwiCoRegulationSummary, txSwiCoRfProbeFail, txSwiCoRcbFail, txSwiCoHwLocal, 
                txSwiCoHwLink, txSwiCoHwWarn, txSwiCoHwFault }
            STATUS current
            DESCRIPTION 
                "Switchless Combiner notifications group."
            ::= { rsXx9TxGroups 111 }

        
        txNotifyActiveReserve NOTIFICATION-GROUP
            NOTIFICATIONS { txActiveReserveExcAutoSummary, txActiveReserveExcAutoReady, txActiveReserveExcAutoSwitchedOver, txActiveReserveExcAutoRfSwitchSummary, txActiveReserveOstAutoSummary, 
                txActiveReserveOstAutoReady, txActiveReserveOstAutoSwitchedOver, txActiveReserveOstAutoRfSwitchSummary, txActiveReserveExcAutoOn, txActiveReserveOstAutoOn
                 }
            STATUS current
            DESCRIPTION 
                "Active Reserve notifications group."
            ::= { rsXx9TxGroups 112 }

        
        txNotifyInputSatFeed NOTIFICATION-GROUP
            NOTIFICATIONS { txInpIfSatInfoPacket, txInpIfSatPacketLength, txInpIfSatTransponderLocked, txInpIfSatIpOutput, txInpIfSatBtsStatus, 
                txInpIfSatCarrierNoiseStatus, txInpIfSatLinkMarginStatus, txInpIfSatDriftStatus, txInpIfSatStreamTsIdMatch, txInpIfSatReceiverState, 
                txInpIfSatInputState }
            STATUS current
            DESCRIPTION 
                "SAT receiver notifications group."
            ::= { rsXx9TxGroups 113 }

        
        txNotifyRfSensors NOTIFICATION-GROUP
            NOTIFICATIONS { txRfSensorLinkStatus, txRfSensorCalibrated }
            STATUS current
            DESCRIPTION 
                "Rf sensor notifications group."
            ::= { rsXx9TxGroups 114 }

        
        txNotifyPaTLx NOTIFICATION-GROUP
            NOTIFICATIONS { txAmpSummary, txAmpOn, txAmpMute, txAmpTemperatureFail }
            STATUS current
            DESCRIPTION 
                "Tlx power amplifier notifications group."
            ::= { rsXx9TxGroups 115 }

        
        txObjsExciterAutomatic OBJECT-GROUP
            OBJECTS { txTransCmdReserveOpMode }
            STATUS current
            DESCRIPTION 
                "Exciter automatic objects group."
            ::= { rsXx9TxGroups 201 }

        
        txObjsDualDrive OBJECT-GROUP
            OBJECTS { txExcAutoPreselectExcA, txExcAutoPreselectExcB, txExcAutoOperationMode, txExciterAutomaticMode, txExcAutoGuardTime, 
                txExcAutoPreselected, txExcAutoRfSwitchPosition }
            STATUS current
            DESCRIPTION 
                "DualDrive and BackupDrive configuration objects."
            ::= { rsXx9TxGroups 202 }

        
        txObjsSFN1 OBJECT-GROUP
            OBJECTS { txSfnStateNetworkDelay, txSfnStateMaximumDelay, txSfnStateDispatchTime }
            STATUS current
            DESCRIPTION 
                "SFN objects for DVB-T, ISDB-T, DTMB, ATSC only."
            ::= { rsXx9TxGroups 203 }

        
        txObjsSFN2 OBJECT-GROUP
            OBJECTS { txSfnSetupSFN }
            STATUS current
            DESCRIPTION 
                "SFN objects not for ISDB-T."
            ::= { rsXx9TxGroups 204 }

        
        txObjsPMx OBJECT-GROUP
            OBJECTS { txPmxFanFail, txPmxInletAirTemperature, txPmxOutletAirTemperature, txPmxFreqIDString, txAmpStI1A, 
                txAmpStI2A, txAmpStI3A, txAmpStI1B, txAmpStI2B, txAmpStI3B
                 }
            STATUS current
            DESCRIPTION 
                "PMU and PMV specific objects"
            ::= { rsXx9TxGroups 205 }

        
        txObjsNonFM OBJECT-GROUP
            OBJECTS { txInpAutoPreferredInput, txInpAutoMuteOnInputFail, txInpAutoFailDetection }
            STATUS current
            DESCRIPTION 
                "Objects for all modulation modes except FM."
            ::= { rsXx9TxGroups 207 }

        
        txObjsPHR901 OBJECT-GROUP
            OBJECTS { txPhr901PwrIn, txPhr901PwrDrv, txPhr901I12, txPhr901I34, txPhr901I56, 
                txPhr901I78 }
            STATUS current
            DESCRIPTION 
                "PHR901 specific objects"
            ::= { rsXx9TxGroups 208 }

        
        txObjsNonBand2 OBJECT-GROUP
            OBJECTS { txInpAutoInputFailDelay, txInpAutoSeamlessOpMode, txInpAutoSeamlessPossible }
            STATUS current
            DESCRIPTION 
                "Non band II objects."
            ::= { rsXx9TxGroups 209 }

        
        txObjsPMV901 OBJECT-GROUP
            OBJECTS { txPmxDohertyActive }
            STATUS current
            DESCRIPTION 
                "PMV901 specific objects"
            ::= { rsXx9TxGroups 210 }

        
        txObjsPMU901 OBJECT-GROUP
            OBJECTS { txPmxFrequencyFail }
            STATUS current
            DESCRIPTION 
                "PMU901 specific objects"
            ::= { rsXx9TxGroups 211 }

        
        txObjsPHx902 OBJECT-GROUP
            OBJECTS { txAmpStI3B, txAmpStI2B, txAmpStI1B, txAmpStI3A, txAmpStI2A, 
                txAmpStI1A, txPhxDohertyActive, txPhxFreqIDString }
            STATUS current
            DESCRIPTION 
                "PHU902, PHU903 and PHV902 specific objects"
            ::= { rsXx9TxGroups 212 }

        
        txObjsNonAtv OBJECT-GROUP
            OBJECTS { txTransStPaEfficiency }
            STATUS current
            DESCRIPTION 
                "Non ATV objects."
            ::= { rsXx9TxGroups 213 }

        
        txObjsTransparentTs OBJECT-GROUP
            OBJECTS { txInpAutoTransparentTs }
            STATUS current
            DESCRIPTION 
                "Transparent TS objects. (DVB-T only)"
            ::= { rsXx9TxGroups 214 }

        
        txObjsNonAnalog OBJECT-GROUP
            OBJECTS { txInpAutoDetectLostPackets }
            STATUS current
            DESCRIPTION 
                "Non FM or ATV objects."
            ::= { rsXx9TxGroups 215 }

        
        txObjsDvbt2 OBJECT-GROUP
            OBJECTS { txSfnStateTimestampState }
            STATUS current
            DESCRIPTION 
                "DVB-T2 specific objects."
            ::= { rsXx9TxGroups 216 }

        
        txObjsPaTlx OBJECT-GROUP
            OBJECTS { txAmpNotificationName, txAmpNotificationMask, txAmpNotificationPriority, txAmpNotificationState, txAmpStPwrOut, 
                txAmpStReflOut, txAmpStVPlusMon, txAmpTlxFanFail, txAmpStTemperature, txAmpTlxV12Mon, 
                txAmpTlxSupplyFail }
            STATUS current
            DESCRIPTION 
                "TLx power amplifier specific objects."
            ::= { rsXx9TxGroups 217 }

        
        txObjsPHU901 OBJECT-GROUP
            OBJECTS { txAmpStI1A, txAmpStI2A, txAmpStI3A, txAmpStI1B, txAmpStI2B, 
                txAmpStI3B }
            STATUS current
            DESCRIPTION 
                "PHU901 specific objects."
            ::= { rsXx9TxGroups 218 }

        
        txObjsPMU905 OBJECT-GROUP
            OBJECTS { txPmxDohertyActive }
            STATUS current
            DESCRIPTION 
                "PMU905 specific objects"
            ::= { rsXx9TxGroups 219 }

        
        txObjsLinPrecorrection OBJECT-GROUP
            OBJECTS { txPrecorrLinStateStatus, txPrecorrLinStateSignalLevel, txPrecorrLinStateAmplitudeRipple, txPrecorrLinStateGroupDelayRipple, txPrecorrLinStateAmplitudeRippleLimit, 
                txPrecorrLinStateGroupDelayRippleLimit, txPrecorrLinSetupOpMode, txPrecorrLinSetupReset, txPrecorrLinSetupAmplitudeRippleLimit, txPrecorrLinSetupGroupDelayRippleLimit, 
                txPrecorrLinSetupEquipmentSlope }
            STATUS current
            DESCRIPTION 
                "Linear precorrection objects group."
            ::= { rsXx9TxGroups 220 }

        
        txObjsNonLinPrecorrection OBJECT-GROUP
            OBJECTS { txPrecorrNonLinStateStatus, txPrecorrNonLinStateSignalLevel, txPrecorrNonLinStateShoulderLeft, txPrecorrNonLinStateShoulderRight, txPrecorrNonLinSetupOpMode, 
                txPrecorrNonLinSetupReset, txPrecorrNonLinSetupShoulderDistance }
            STATUS current
            DESCRIPTION 
                "Nonlinear precorrection objects group."
            ::= { rsXx9TxGroups 221 }

        
        txObjsPrecorrectionCfr OBJECT-GROUP
            OBJECTS { txPrecorrCfrEnable, txPrecorrCfrLevel, txPrecorrCfrInbandNoise, txPrecorrCfrOutbandNoise }
            STATUS current
            DESCRIPTION 
                "Crest factor reduction objects group."
            ::= { rsXx9TxGroups 222 }

        
        txObjsInputExgine OBJECT-GROUP
            OBJECTS { txExgineMode, txExgineStatus, txExgineMute, txExgineSyncInputSrc, txExgineSyncInputStatus, 
                txExgineMpxInput, txExgineE2xInput, txExgineSupply1Status, txExgineSupply2Status }
            STATUS current
            DESCRIPTION 
                "Description."
            ::= { rsXx9TxGroups 223 }

        
        txObjsSignalQuality OBJECT-GROUP
            OBJECTS { txPrecorrSigQualPapr, txPrecorrSigQualMer, txPrecorrSigQualMerWarnLimit }
            STATUS current
            DESCRIPTION 
                "Signal Quality objects group."
            ::= { rsXx9TxGroups 224 }

        
        txObjsDigitalHighPower OBJECT-GROUP
            OBJECTS { txExcCmdRfSlope }
            STATUS current
            DESCRIPTION 
                "Non TLx objects (THx, TMx) and non Band-II."
            ::= { rsXx9TxGroups 225 }

        
        txObjsOutputStageNonTlx OBJECT-GROUP
            OBJECTS { txOstCmdDcControl }
            STATUS current
            DESCRIPTION 
                "Output stage objects group for medium and high power."
            ::= { rsXx9TxGroups 226 }

        
        txNotifyExciterAutomatic NOTIFICATION-GROUP
            NOTIFICATIONS { txExciterAutomaticSwitchedOver, txExciterAutomaticRfSwitchSummary, txExciterAutomaticSummary, txExciterAutomaticReady, txExciterAutomaticOn
                 }
            STATUS current
            DESCRIPTION 
                "Exciter automatic notifications group."
            ::= { rsXx9TxGroups 300 }

        
        txNotifyLinPrecorrection NOTIFICATION-GROUP
            NOTIFICATIONS { txPrecorrLinSummary }
            STATUS current
            DESCRIPTION 
                "Linear precorrection notifications group."
            ::= { rsXx9TxGroups 301 }

        
        txNotifyNonLinPrecorrection NOTIFICATION-GROUP
            NOTIFICATIONS { txPrecorrNonLinSummary }
            STATUS current
            DESCRIPTION 
                "Nonlinear precorrection notifications group."
            ::= { rsXx9TxGroups 302 }

        
        txNotifySignalQuality NOTIFICATION-GROUP
            NOTIFICATIONS { txPrecorrMerState }
            STATUS current
            DESCRIPTION 
                "Signal quality notifications group."
            ::= { rsXx9TxGroups 303 }

        
        txObjsPMxObsoleted OBJECT-GROUP
            OBJECTS { txPmxFreqID, txPmxvRefPowerMax, txPmxAirFilterFail }
            STATUS obsolete
            DESCRIPTION 
                "obsolete PMU and PMV specific objects"
            ::= { rsXx9TxGroups 400 }

        
        txObjsPHxObsoleted OBJECT-GROUP
            OBJECTS { txPhxFreqID }
            STATUS obsolete
            DESCRIPTION 
                "obsolete PHU and PHV specific objects"
            ::= { rsXx9TxGroups 401 }

        
        txObjsInputAutomaticObsoleted OBJECT-GROUP
            OBJECTS { txInpAutoMaxDelayInput1To2 }
            STATUS obsolete
            DESCRIPTION 
                "obsolete Input automatic objects group."
            ::= { rsXx9TxGroups 402 }

        
        txObjsAmplifierObsoleted OBJECT-GROUP
            OBJECTS { txAmpStVReg, txPhr901PwrA, txPhr901PwrB, txPhr901PwrOutAv, txPhr901ReflOutAv, 
                txPhr901PwrAbs }
            STATUS obsolete
            DESCRIPTION 
                "obsolete common amplifier objects group."
            ::= { rsXx9TxGroups 403 }

        
        txObjsInputSatFeedObsoleted OBJECT-GROUP
            OBJECTS { txSatFeedInputServiceDecryptedAt, txSatBtsDecompEnable, txSatBtsRegionalization }
            STATUS obsolete
            DESCRIPTION 
                "obsoleted SAT receiver notifications group."
            ::= { rsXx9TxGroups 404 }

        
        txObjsPrecorrectionObsoleted OBJECT-GROUP
            OBJECTS { txPrecorrNonLinSetupSignalLimit }
            STATUS obsolete
            DESCRIPTION 
                "Obsoleted precorrection objects group."
            ::= { rsXx9TxGroups 405 }

        
        txNotifyAmplifierObsoleted NOTIFICATION-GROUP
            NOTIFICATIONS { txAmpDriverFail }
            STATUS obsolete
            DESCRIPTION 
                "obsolete Amplifier Notification group."
            ::= { rsXx9TxGroups 500 }

        
    
    END

--
-- RS-XX9-TX-MIB.mi2
--
