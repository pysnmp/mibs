--
-- IRT-FM-SINGLETRANSMITTER-MIB.my
-- MIB generated by MG-SOFT Visual MIB Builder Version 6.0  Build 88
-- Friday, May 04, 2007 at 18:41:10
--

	IRT-FM-SINGLETRANSMITTER-MIB DEFINITIONS ::= BEGIN
 
		IMPORTS
			eventTimeStamp, eventPriority, eventCounter, mibRelease			
				FROM IRT-COMMONVARBINDS-MIB			
			fm, SelectOnOff, PresentNotPresent, FaultOK, WarningOK, 
			LocalRemote			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			TruthValue			
				FROM SNMPv2-TC;
	
	
		-- 1.3.6.1.4.1.19831.1.1.3.1
		fmSingleTransmitter MODULE-IDENTITY 
			LAST-UPDATED "200705041400Z"		-- May 04, 2007 at 14:00 GMT
			ORGANIZATION 
				"IRT for WORKING-GROUP-TC-MIB"
			CONTACT-INFO 
				"Contact-info.
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				
				FM Single Transmitter
				
				branch definition
				
				1st level
				
				events              OBJECT IDENTIFIER ::= { fmSingleTransmitter 0 }
				fmSTGeneral         OBJECT IDENTIFIER ::= { fmSingleTransmitter 1 }
				fmSTEventEnable     OBJECT IDENTIFIER ::= { fmSingleTransmitter 2 }
				fmSTEventPriority   OBJECT IDENTIFIER ::= { fmSingleTransmitter 3 }
				groups              OBJECT IDENTIFIER ::= { fmSingleTransmitter 4 }
				
				2nd level
				
				fmSTEventEnableGeneral     OBJECT IDENTIFIER ::= { fmSTEventEnable 1 }
				fmSTEventPriorityGeneral   OBJECT IDENTIFIER ::= { fmSTEventPriority 1 }
				
				end branch
				
				
				"
			REVISION "200705041400Z"		-- May 04, 2007 at 14:00 GMT
			DESCRIPTION 
				"change LocalMode (description) and Module-COMPLIANCE"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { fm 1 }

		
	
	
--
-- Node definitions
--
	
-- fm events single transmitter
		-- 1.3.6.1.4.1.19831.1.1.3.1.0
		fmEventsST OBJECT IDENTIFIER ::= { fmSingleTransmitter 0 }

		
		-- 1.3.6.1.4.1.19831.1.1.3.1.0.1
		fmSTTransmitterOpModeEvent NOTIFICATION-TYPE
			OBJECTS { sysDescr, sysName, sysLocation, eventTimeStamp, eventPriority, 
				eventCounter, fmSTTransmitterOpMode }
			STATUS current
			DESCRIPTION 
				"Description. fmSTTransmitterOpMode notification"
			::= { fmEventsST 1 }

		
		-- 1.3.6.1.4.1.19831.1.1.3.1.0.2
		fmSTRFPresentEvent NOTIFICATION-TYPE
			OBJECTS { sysDescr, sysName, sysLocation, eventTimeStamp, eventPriority, 
				eventCounter, fmSTRFPresent }
			STATUS current
			DESCRIPTION 
				"Description. fmSTRFPresent notification"
			::= { fmEventsST 2 }

		
		-- 1.3.6.1.4.1.19831.1.1.3.1.0.3
		fmSTFaultEvent NOTIFICATION-TYPE
			OBJECTS { sysDescr, sysName, sysLocation, eventTimeStamp, eventPriority, 
				eventCounter, fmSTFault }
			STATUS current
			DESCRIPTION 
				"Description. fmSTFault notification"
			::= { fmEventsST 3 }

		
		-- 1.3.6.1.4.1.19831.1.1.3.1.0.4
		fmSTWarningEvent NOTIFICATION-TYPE
			OBJECTS { sysDescr, sysName, sysLocation, eventTimeStamp, eventPriority, 
				eventCounter, fmSTWarning }
			STATUS current
			DESCRIPTION 
				"Description. fmSTWarning notification"
			::= { fmEventsST 4 }

		
		-- 1.3.6.1.4.1.19831.1.1.3.1.0.5
		fmSTLocalModeEvent NOTIFICATION-TYPE
			OBJECTS { sysDescr, sysName, sysLocation, eventTimeStamp, eventPriority, 
				eventCounter, fmSTLocalMode }
			STATUS current
			DESCRIPTION 
				"Description. fmSTLocalMode notification"
			::= { fmEventsST 5 }

		
-- fm general
		-- 1.3.6.1.4.1.19831.1.1.3.1.1
		fmSTGeneral OBJECT IDENTIFIER ::= { fmSingleTransmitter 1 }

		
		-- 1.3.6.1.4.1.19831.1.1.3.1.1.1
		fmSTTransmitterOpMode OBJECT-TYPE
			SYNTAX SelectOnOff
			UNITS " "
			MAX-ACCESS read-write
			STATUS current
			DESCRIPTION
				"Single transmitter. Transmitter control of single  transmitter
				
				(0) undefined
				(1) ON
				(2) OFF"
			::= { fmSTGeneral 1 }

		
		-- 1.3.6.1.4.1.19831.1.1.3.1.1.2
		fmSTRFPresent OBJECT-TYPE
			SYNTAX PresentNotPresent
			MAX-ACCESS read-only
			STATUS current
			DESCRIPTION
				"Single  transmitter. Describes if  the output power is present
				
				(0) undefined
				(1) present
				(2) not present
				"
			::= { fmSTGeneral 2 }

		
		-- 1.3.6.1.4.1.19831.1.1.3.1.1.3
		fmSTFault OBJECT-TYPE
			SYNTAX FaultOK
			MAX-ACCESS read-only
			STATUS current
			DESCRIPTION
				"Single transmitter. Fault state of transmitter
				
				(0) undefined
				(1) fault
				(2) ok"
			::= { fmSTGeneral 3 }

		
		-- 1.3.6.1.4.1.19831.1.1.3.1.1.4
		fmSTWarning OBJECT-TYPE
			SYNTAX WarningOK
			MAX-ACCESS read-only
			STATUS current
			DESCRIPTION
				"Single transmitter. Warning state of single transmitter
				
				(0) undefined
				(1) warning
				(2) ok"
			::= { fmSTGeneral 4 }

		
		-- 1.3.6.1.4.1.19831.1.1.3.1.1.5
		fmSTLocalMode OBJECT-TYPE
			SYNTAX LocalRemote
			MAX-ACCESS read-only
			STATUS current
			DESCRIPTION
				"Single transmitter. Local  mode
				
				(0) undefined
				(1) local
				(2) remote"
			::= { fmSTGeneral 5 }

		
-- fm single transmitter: switch for event
		-- 1.3.6.1.4.1.19831.1.1.3.1.2
		fmSTEventEnable OBJECT IDENTIFIER ::= { fmSingleTransmitter 2 }

		
-- single transmitter: switch for event generall
		-- 1.3.6.1.4.1.19831.1.1.3.1.2.1
		fmSTEventEnableGeneral OBJECT IDENTIFIER ::= { fmSTEventEnable 1 }

		
		-- 1.3.6.1.4.1.19831.1.1.3.1.2.1.1
		fmSTTransmitterOpModeEnable OBJECT-TYPE
			SYNTAX TruthValue
			MAX-ACCESS read-write
			STATUS current
			DESCRIPTION
				"Description.Enable/Disable switch for fmSTTransmitterOpMode event"
			::= { fmSTEventEnableGeneral 1 }

		
		-- 1.3.6.1.4.1.19831.1.1.3.1.2.1.2
		fmSTFRFPresentEnable OBJECT-TYPE
			SYNTAX TruthValue
			MAX-ACCESS read-write
			STATUS current
			DESCRIPTION
				"Description.Enable/Disable switch for fmSTRFPresent event"
			::= { fmSTEventEnableGeneral 2 }

		
		-- 1.3.6.1.4.1.19831.1.1.3.1.2.1.3
		fmSTFaultEnable OBJECT-TYPE
			SYNTAX TruthValue
			MAX-ACCESS read-write
			STATUS current
			DESCRIPTION
				"Description.Enable/Disable switch for fmSTRFPresent event"
			::= { fmSTEventEnableGeneral 3 }

		
		-- 1.3.6.1.4.1.19831.1.1.3.1.2.1.4
		fmSTWarningEnable OBJECT-TYPE
			SYNTAX TruthValue
			MAX-ACCESS read-write
			STATUS current
			DESCRIPTION
				"Description.Enable/Disable switch for fmSTWarning event"
			::= { fmSTEventEnableGeneral 4 }

		
		-- 1.3.6.1.4.1.19831.1.1.3.1.2.1.5
		fmSTLocalModeEnable OBJECT-TYPE
			SYNTAX TruthValue
			MAX-ACCESS read-write
			STATUS current
			DESCRIPTION
				"Description.Enable/Disable switch for fmSTLocalMode event"
			::= { fmSTEventEnableGeneral 5 }

		
-- fm single transmitter: event priority
		-- 1.3.6.1.4.1.19831.1.1.3.1.3
		fmSTEventPriority OBJECT IDENTIFIER ::= { fmSingleTransmitter 3 }

		
-- fm single transmitter: general event priority
		-- 1.3.6.1.4.1.19831.1.1.3.1.3.1
		fmSTEventPriorityGeneral OBJECT IDENTIFIER ::= { fmSTEventPriority 1 }

		
		-- 1.3.6.1.4.1.19831.1.1.3.1.3.1.1
		fmSTTransmitterOpModePriority OBJECT-TYPE
			SYNTAX Unsigned32
			MAX-ACCESS read-write
			STATUS current
			DESCRIPTION
				"Description.Priority for fmSTTransmitterOpMode event"
			::= { fmSTEventPriorityGeneral 1 }

		
		-- 1.3.6.1.4.1.19831.1.1.3.1.3.1.2
		fmSTRFPresentPriority OBJECT-TYPE
			SYNTAX Unsigned32
			MAX-ACCESS read-write
			STATUS current
			DESCRIPTION
				"Description.Priority for fmSTRFPresent event"
			::= { fmSTEventPriorityGeneral 2 }

		
		-- 1.3.6.1.4.1.19831.1.1.3.1.3.1.3
		fmSTFaultPriority OBJECT-TYPE
			SYNTAX Unsigned32
			MAX-ACCESS read-write
			STATUS current
			DESCRIPTION
				"Description.Priority for fmSTFault event"
			::= { fmSTEventPriorityGeneral 3 }

		
		-- 1.3.6.1.4.1.19831.1.1.3.1.3.1.4
		fmSTWarningPriority OBJECT-TYPE
			SYNTAX Unsigned32
			MAX-ACCESS read-write
			STATUS current
			DESCRIPTION
				"Description.Priority for fmSTWarning event"
			::= { fmSTEventPriorityGeneral 4 }

		
		-- 1.3.6.1.4.1.19831.1.1.3.1.3.1.5
		fmSTLocalModePriority OBJECT-TYPE
			SYNTAX Unsigned32
			MAX-ACCESS read-write
			STATUS current
			DESCRIPTION
				"Description.Priority for fmSTLocalMode event"
			::= { fmSTEventPriorityGeneral 5 }

		
		-- 1.3.6.1.4.1.19831.1.1.3.1.4
		groupsST OBJECT IDENTIFIER ::= { fmSingleTransmitter 4 }

		
		-- 1.3.6.1.4.1.19831.1.1.3.1.4.1
		objectGroupST OBJECT-GROUP
			OBJECTS { fmSTTransmitterOpMode, fmSTRFPresent, fmSTFault, fmSTWarning, fmSTLocalMode, 
				fmSTTransmitterOpModeEnable, fmSTFaultEnable, fmSTWarningEnable, fmSTLocalModeEnable, fmSTTransmitterOpModePriority, 
				fmSTRFPresentPriority, fmSTFaultPriority, fmSTWarningPriority, fmSTLocalModePriority, fmSTFRFPresentEnable
				 }
			STATUS current
			DESCRIPTION 
				"Description. fm single transmitter  objects"
			::= { groupsST 1 }

		
		-- 1.3.6.1.4.1.19831.1.1.3.1.4.2
		eventGroupST NOTIFICATION-GROUP
			NOTIFICATIONS { fmSTLocalModeEvent, fmSTWarningEvent, fmSTFaultEvent, fmSTRFPresentEvent, fmSTTransmitterOpModeEvent
				 }
			STATUS current
			DESCRIPTION 
				"Description. fm single transmitter  events"
			::= { groupsST 2 }

		
		-- 1.3.6.1.4.1.19831.1.1.3.1.5
		complianceST OBJECT IDENTIFIER ::= { fmSingleTransmitter 5 }

		
		-- 1.3.6.1.4.1.19831.1.1.3.1.5.1
		fmSingleTransmitterCompliance MODULE-COMPLIANCE
			STATUS current
			DESCRIPTION 
				"Compliance Statement"
			MODULE -- this module
				MANDATORY-GROUPS { objectGroupST, eventGroupST }
			::= { complianceST 1 }

		
	
	END

--
-- IRT-FM-SINGLETRANSMITTER-MIB.my
--
