--
-- RS-XX9-SMI-MIB.mi2
-- MIB generated by MG-SOFT Visual MIB Builder 2010 Version 8.0  Build 403
-- Wednesday, June 04, 2014 at 14:44:13
--

-- *****************************************************************************
-- *****************************************************************************
-- **
-- **  COPYRIGHT      (c) 2011 Rohde & Schwarz GmbH & Co. KG
-- **                          Muehldorfstrasse 15
-- **    R & S                 D-81671 Muenchen
-- **
-- *****************************************************************************
-- **
-- **  MODULE         RS-XX9-SMI-MIB
-- **  
-- *****************************************************************************
-- *****************************************************************************

    RS-XX9-SMI-MIB DEFINITIONS ::= BEGIN
 
        IMPORTS
            rsProdBroadcastTransmitter, rsRegModules            
                FROM RS-COMMON-MIB            
            MODULE-IDENTITY, OBJECT-IDENTITY            
                FROM SNMPv2-SMI;
    
    
        rsXx9MibModule MODULE-IDENTITY 
            LAST-UPDATED "201305291521Z"		-- May 29, 2013 at 15:21 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines high level nodes for the organization of all RS-XX9 MIBs.
                It is intended to be IMPORT'ed by all other RS-XX9 MIBs.
                
                The following MIBs are related to this:
                - RS-COMMON-MIB         - mandatory for this MIB."
            REVISION "201305291521Z"		-- May 29, 2013 at 15:21 GMT
            DESCRIPTION 
                "rsXx9Dtmb added"
            REVISION "201108160800Z"		-- August 16, 2011 at 08:00 GMT
            DESCRIPTION 
                "Initial revision."
            ::= { rsRegModules 216 }

        
    
--
-- Node definitions
--
    
        rsXx9Mib OBJECT-IDENTITY
            STATUS current
            DESCRIPTION 
                "All RS-XX9 MIBs are organized under this node."
            ::= { rsProdBroadcastTransmitter 216 }

        
        rsXx9Common OBJECT-IDENTITY
            STATUS current
            DESCRIPTION 
                "Root node for the RS-XX9-COMMON-MIB."
            ::= { rsXx9Mib 2 }

        
        rsXx9Tx OBJECT-IDENTITY
            STATUS current
            DESCRIPTION 
                "Root node for the RS-XX9-TX-MIB."
            ::= { rsXx9Mib 3 }

        
        rsXx9MTx OBJECT-IDENTITY
            STATUS current
            DESCRIPTION 
                "Root node for the RS-XX9-MTX-MIB."
            ::= { rsXx9Mib 4 }

        
        rsXx9DvbT2 OBJECT-IDENTITY
            STATUS current
            DESCRIPTION 
                "Root node for the RS-XX9-DVBT2-MIB."
            ::= { rsXx9Mib 5 }

        
        rsXx9DvbT OBJECT-IDENTITY
            STATUS current
            DESCRIPTION 
                "Root node for the RS-XX9-DVBT-MIB."
            ::= { rsXx9Mib 6 }

        
        rsXx9Atsc OBJECT-IDENTITY
            STATUS current
            DESCRIPTION 
                "Root node for the RS-XX9-ATSC-MIB."
            ::= { rsXx9Mib 7 }

        
        rsXx9IsdbT OBJECT-IDENTITY
            STATUS current
            DESCRIPTION 
                "Root node for the RS-XX9-ISDBT-MIB."
            ::= { rsXx9Mib 8 }

        
        rsXx9Atv OBJECT-IDENTITY
            STATUS current
            DESCRIPTION 
                "Root node for the RS-XX9-ATV-MIB."
            ::= { rsXx9Mib 9 }

        
        rsXx9Dab OBJECT-IDENTITY
            STATUS current
            DESCRIPTION 
                "Root node for the RS-XX9-DAB-MIB."
            ::= { rsXx9Mib 10 }

        
        rsXx9Fm OBJECT-IDENTITY
            STATUS current
            DESCRIPTION 
                "Root node for the RS-XX9-FM-MIB."
            ::= { rsXx9Mib 11 }

        
        rsXx9Dtmb OBJECT-IDENTITY
            STATUS current
            DESCRIPTION 
                "Root node for the RS-XX9-DTMB-MIB."
            ::= { rsXx9Mib 12 }

        
        rsXx9LiquidCooling OBJECT-IDENTITY
            STATUS current
            DESCRIPTION 
                "Root node for the RS-XX9-LIQUID-COOLING-MIB."
            ::= { rsXx9Mib 100 }

        
        rsXx9AirCooling OBJECT-IDENTITY
            STATUS current
            DESCRIPTION 
                "Root node for the RS-XX9-AIR-COOLING-MIB."
            ::= { rsXx9Mib 101 }

        
    
    END

--
-- RS-XX9-SMI-MIB.mi2
--
