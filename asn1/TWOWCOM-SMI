--
-- TWOWCOM-SMI.my
-- MIB generated by MG-SOFT Visual MIB Builder Version 6.0  Build 88
-- Monday, April 27, 2009 at 14:28:21
--

	TWOWCOM-SMI DEFINITIONS ::= BEGIN
 
		IMPORTS
			enterprises, MODULE-IDENTITY			
				FROM SNMPv2-SMI;
	
	
		-- 1.3.6.1.4.1.21529
		twowcom MODULE-IDENTITY 
			LAST-UPDATED "201106231200Z"		-- June 23, 2011 at 12:00 GMT
			ORGANIZATION 
				"2wcom GmbH"
			CONTACT-INFO 
				"2wcom GmbH
				c/o Martin Hoppe
				Lise-Meitner-Str. 4
				24941 Flensburg
				Germany
								
				Tel: +49 461 662830-35
				Fax: +49 461 662830-11
								
				WEB: www.2wcom.com
				"
			DESCRIPTION 
				"2wcom MIB Modul"
			REVISION "201106231200Z"		-- June 23, 2011 at 12:00 GMT
			DESCRIPTION 
				"Version V0.5
				- new object tree dvbMultiplexer (1.3.6.1.4.1.21529.3.3)"
			REVISION "200904271425Z"		-- April 27, 2009 at 14:25 GMT
			DESCRIPTION 
				"Version V0.4
				- new object tree generator (1.3.6.1.4.1.21529.4)"
			REVISION "200802191037Z"		-- February 19, 2008 at 10:37 GMT
			DESCRIPTION 
				"Version V0.3
				- new object tree dvb (1.3.6.1.4.1.21529.3)"
			REVISION "200610261604Z"		-- October 26, 2006 at 16:04 GMT
			DESCRIPTION 
				"Version V0.2
				- all textual conventions moved to the TWOWCOM-COMMONVARBINS Mib.
				"
			REVISION "200606011151Z"		-- June 01, 2006 at 11:51 GMT
			DESCRIPTION 
				"Version V0.1"
			::= { enterprises 21529 }

		
	
--
-- Node definitions
--
		-- 1.3.6.1.4.1.21529.1
		encoder OBJECT IDENTIFIER ::= { twowcom 1 }

		
		-- 1.3.6.1.4.1.21529.2
		decoder OBJECT IDENTIFIER ::= { twowcom 2 }

		
		-- 1.3.6.1.4.1.21529.3
		dvb OBJECT IDENTIFIER ::= { twowcom 3 }

		
		-- 1.3.6.1.4.1.21529.3.1
		dvbEncoder OBJECT IDENTIFIER ::= { dvb 1 }

		
		-- 1.3.6.1.4.1.21529.3.2
		dvbDecoder OBJECT IDENTIFIER ::= { dvb 2 }

		
		-- 1.3.6.1.4.1.21529.3.3
		dvbMultiplexer OBJECT IDENTIFIER ::= { dvb 3 }

		
		-- 1.3.6.1.4.1.21529.4
		generator OBJECT IDENTIFIER ::= { twowcom 4 }

		
		-- 1.3.6.1.4.1.21529.10
		other OBJECT IDENTIFIER ::= { twowcom 10 }

		
	
	END

--
-- TWOWCOM-SMI.my
--
