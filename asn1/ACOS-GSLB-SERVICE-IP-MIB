ACOS-GSLB-SERVICE-IP-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		gslbServiceIpModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "gslbServiceIpModule OID for ACOS"
				::=  {  acosSchema 424 }

serviceIp		 OBJECT IDENTIFIER ::= { gslbServiceIpModule 1}

serviceIpStatsTable OBJECT-TYPE
	 SYNTAX SEQUENCE OF ServiceIpStatsEntry
	 MAX-ACCESS not-accessible
	 STATUS current
	 DESCRIPTION
	 "Service IP from object 'gslb.service-ip'"
	::= {serviceIp 1}

serviceIpStatsEntry OBJECT-TYPE
	SYNTAX ServiceIpStatsEntry
	MAX-ACCESS not-accessible
	STATUS current
	DESCRIPTION
		"The serviceIpStats stats entry"
	INDEX {
		serviceIpStatsSlotId,
		serviceIpStatsNodeName
	}
	::= { serviceIpStatsTable 1 }

ServiceIpStatsEntry ::=
	SEQUENCE {
		serviceIpStatsSlotId Integer32,
		serviceIpStatsNodeName DisplayString,
		serviceIpStatsHits	 CounterBasedGauge64,
		serviceIpStatsRecent	 CounterBasedGauge64
	}

serviceIpStatsSlotId OBJECT-TYPE
	 SYNTAX Integer32
	 MAX-ACCESS read-only
	 STATUS current
	 DESCRIPTION
		 ""
	::= { serviceIpStatsEntry 1 }

serviceIpStatsNodeName OBJECT-TYPE
	 SYNTAX DisplayString
	 MAX-ACCESS read-only
	 STATUS current
	 DESCRIPTION
		 "node-name"
	::= { serviceIpStatsEntry 2 }

serviceIpStatsHits OBJECT-TYPE
	 SYNTAX Integer32
	 MAX-ACCESS read-only
	 STATUS current
	 DESCRIPTION
		 "hits"
	::= { serviceIpStatsEntry 3 }

serviceIpStatsRecent OBJECT-TYPE
	 SYNTAX Integer32
	 MAX-ACCESS read-only
	 STATUS current
	 DESCRIPTION
		 "recent"
	::= { serviceIpStatsEntry 4 }

serviceIpOperTable OBJECT-TYPE
	 SYNTAX SEQUENCE OF ServiceIpOperEntry
	 MAX-ACCESS not-accessible
	 STATUS current
	 DESCRIPTION
		 "Service IP from object 'gslb.service-ip'"
	::= {serviceIp 2}

serviceIpOperEntry OBJECT-TYPE
	SYNTAX ServiceIpOperEntry
	MAX-ACCESS not-accessible
	STATUS current
	DESCRIPTION
		"The serviceIpOper entry"
	INDEX {
		serviceIpOperSlotId,
		serviceIpOperNodeName
	}
	::= { serviceIpOperTable 1 }

ServiceIpOperEntry ::=
	SEQUENCE {
		serviceIpOperSlotId Integer32,
		serviceIpOperNodeName DisplayString,
		serviceIpOperServiceIp	 DisplayString,
		serviceIpOperIp	 DisplayString,
		serviceIpOperState	 DisplayString,
		serviceIpOperPortCount	 Integer32,
		serviceIpOperVirtualServer	 Integer32,
		serviceIpOperDisabled	 Integer32,
		serviceIpOperGslbProtocol	 Integer32,
		serviceIpOperLocalProtocol	 Integer32,
		serviceIpOperManuallyHealthCheck	 Integer32,
		serviceIpOperUseGslbState	 Integer32,
		serviceIpOperDynamic	 Integer32
	}

serviceIpOperSlotId OBJECT-TYPE
	 SYNTAX Integer32
	 MAX-ACCESS read-only
	 STATUS current
	 DESCRIPTION
		 ""
	::= { serviceIpOperEntry 1 }

serviceIpOperNodeName OBJECT-TYPE
	 SYNTAX DisplayString
	 MAX-ACCESS read-only
	 STATUS current
	 DESCRIPTION
		 "node-name"
	::= { serviceIpOperEntry 2 }

serviceIpOperServiceIp OBJECT-TYPE
	 SYNTAX DisplayString
	 MAX-ACCESS read-only
	 STATUS current
	 DESCRIPTION
		 "service-ip"
	::= { serviceIpOperEntry 3 }

serviceIpOperIp OBJECT-TYPE
	 SYNTAX DisplayString
	 MAX-ACCESS read-only
	 STATUS current
	 DESCRIPTION
		 "ip"
	::= { serviceIpOperEntry 4 }

serviceIpOperState OBJECT-TYPE
	 SYNTAX DisplayString
	 MAX-ACCESS read-only
	 STATUS current
	 DESCRIPTION
		 "state"
	::= { serviceIpOperEntry 5 }

serviceIpOperPortCount OBJECT-TYPE
	 SYNTAX Integer32
	 MAX-ACCESS read-only
	 STATUS current
	 DESCRIPTION
		 "port-count"
	::= { serviceIpOperEntry 6 }

serviceIpOperVirtualServer OBJECT-TYPE
	 SYNTAX Integer32
	 MAX-ACCESS read-only
	 STATUS current
	 DESCRIPTION
		 "virtual-server"
	::= { serviceIpOperEntry 7 }

serviceIpOperDisabled OBJECT-TYPE
	 SYNTAX Integer32
	 MAX-ACCESS read-only
	 STATUS current
	 DESCRIPTION
		 "disabled"
	::= { serviceIpOperEntry 8 }

serviceIpOperGslbProtocol OBJECT-TYPE
	 SYNTAX Integer32
	 MAX-ACCESS read-only
	 STATUS current
	 DESCRIPTION
		 "gslb-protocol"
	::= { serviceIpOperEntry 9 }

serviceIpOperLocalProtocol OBJECT-TYPE
	 SYNTAX Integer32
	 MAX-ACCESS read-only
	 STATUS current
	 DESCRIPTION
		 "local-protocol"
	::= { serviceIpOperEntry 10 }

serviceIpOperManuallyHealthCheck OBJECT-TYPE
	 SYNTAX Integer32
	 MAX-ACCESS read-only
	 STATUS current
	 DESCRIPTION
		 "manually-health-check"
	::= { serviceIpOperEntry 11 }

serviceIpOperUseGslbState OBJECT-TYPE
	 SYNTAX Integer32
	 MAX-ACCESS read-only
	 STATUS current
	 DESCRIPTION
		 "use_gslb_state"
	::= { serviceIpOperEntry 12 }

serviceIpOperDynamic OBJECT-TYPE
	 SYNTAX Integer32
	 MAX-ACCESS read-only
	 STATUS current
	 DESCRIPTION
		 "dynamic"
	::= { serviceIpOperEntry 13 }

port		 OBJECT IDENTIFIER ::= { serviceIp 3}

portStatsTable OBJECT-TYPE
	 SYNTAX SEQUENCE OF PortStatsEntry
	 MAX-ACCESS not-accessible
	 STATUS current
	 DESCRIPTION
	 "Server Port from object 'gslb.service-ip.port'"
	::= {port 1}

portStatsEntry OBJECT-TYPE
	SYNTAX PortStatsEntry
	MAX-ACCESS not-accessible
	STATUS current
	DESCRIPTION
		"The portStats stats entry"
	INDEX {
		portStatsSlotId,
		portStatsNodeName,
		portStatsPortNum,
		portStatsPortProto,
		portStatsService
	}
	::= { portStatsTable 1 }

PortStatsEntry ::=
	SEQUENCE {
		portStatsSlotId Integer32,
		portStatsNodeName DisplayString,
		portStatsPortNum Integer32,
		portStatsPortProto DisplayString,
		portStatsService DisplayString,
		portStatsActive	 CounterBasedGauge64,
		portStatsCurrent	 CounterBasedGauge64
	}

portStatsSlotId OBJECT-TYPE
	 SYNTAX Integer32
	 MAX-ACCESS read-only
	 STATUS current
	 DESCRIPTION
		 ""
	::= { portStatsEntry 1 }

portStatsNodeName OBJECT-TYPE
	 SYNTAX DisplayString
	 MAX-ACCESS read-only
	 STATUS current
	 DESCRIPTION
		 "node-name"
	::= { portStatsEntry 2 }

portStatsPortNum OBJECT-TYPE
	 SYNTAX Integer32
	 MAX-ACCESS read-only
	 STATUS current
	 DESCRIPTION
		 "port-num"
	::= { portStatsEntry 3 }

portStatsPortProto OBJECT-TYPE
	 SYNTAX DisplayString
	 MAX-ACCESS read-only
	 STATUS current
	 DESCRIPTION
		 "port-proto"
	::= { portStatsEntry 4 }

portStatsService OBJECT-TYPE
	 SYNTAX DisplayString
	 MAX-ACCESS read-only
	 STATUS current
	 DESCRIPTION
		 "service"
	::= { portStatsEntry 5 }

portStatsActive OBJECT-TYPE
	 SYNTAX Integer32
	 MAX-ACCESS read-only
	 STATUS current
	 DESCRIPTION
		 "active"
	::= { portStatsEntry 6 }

portStatsCurrent OBJECT-TYPE
	 SYNTAX Integer32
	 MAX-ACCESS read-only
	 STATUS current
	 DESCRIPTION
		 "current"
	::= { portStatsEntry 7 }

portOperTable OBJECT-TYPE
	 SYNTAX SEQUENCE OF PortOperEntry
	 MAX-ACCESS not-accessible
	 STATUS current
	 DESCRIPTION
		 "Server Port from object 'gslb.service-ip.port'"
	::= {port 2}

portOperEntry OBJECT-TYPE
	SYNTAX PortOperEntry
	MAX-ACCESS not-accessible
	STATUS current
	DESCRIPTION
		"The portOper entry"
	INDEX {
		portOperSlotId,
		portOperNodeName,
		portOperPortNum,
		portOperPortProto,
		portOperService
	}
	::= { portOperTable 1 }

PortOperEntry ::=
	SEQUENCE {
		portOperSlotId Integer32,
		portOperNodeName DisplayString,
		portOperPortNum Integer32,
		portOperPortProto DisplayString,
		portOperService DisplayString,
		portOperServicePort	 Integer32,
		portOperState	 DisplayString,
		portOperDisabled	 Integer32,
		portOperGslbProtocol	 Integer32,
		portOperLocalProtocol	 Integer32,
		portOperTcp	 Integer32,
		portOperManuallyHealthCheck	 Integer32,
		portOperUseGslbState	 Integer32,
		portOperDynamic	 Integer32
	}

portOperSlotId OBJECT-TYPE
	 SYNTAX Integer32
	 MAX-ACCESS read-only
	 STATUS current
	 DESCRIPTION
		 ""
	::= { portOperEntry 1 }

portOperNodeName OBJECT-TYPE
	 SYNTAX DisplayString
	 MAX-ACCESS read-only
	 STATUS current
	 DESCRIPTION
		 "node-name"
	::= { portOperEntry 2 }

portOperPortNum OBJECT-TYPE
	 SYNTAX Integer32
	 MAX-ACCESS read-only
	 STATUS current
	 DESCRIPTION
		 "port-num"
	::= { portOperEntry 3 }

portOperPortProto OBJECT-TYPE
	 SYNTAX DisplayString
	 MAX-ACCESS read-only
	 STATUS current
	 DESCRIPTION
		 "port-proto"
	::= { portOperEntry 4 }

portOperService OBJECT-TYPE
	 SYNTAX DisplayString
	 MAX-ACCESS read-only
	 STATUS current
	 DESCRIPTION
		 "service"
	::= { portOperEntry 5 }

portOperServicePort OBJECT-TYPE
	 SYNTAX Integer32
	 MAX-ACCESS read-only
	 STATUS current
	 DESCRIPTION
		 "service-port"
	::= { portOperEntry 6 }

portOperState OBJECT-TYPE
	 SYNTAX DisplayString
	 MAX-ACCESS read-only
	 STATUS current
	 DESCRIPTION
		 "state"
	::= { portOperEntry 7 }

portOperDisabled OBJECT-TYPE
	 SYNTAX Integer32
	 MAX-ACCESS read-only
	 STATUS current
	 DESCRIPTION
		 "disabled"
	::= { portOperEntry 8 }

portOperGslbProtocol OBJECT-TYPE
	 SYNTAX Integer32
	 MAX-ACCESS read-only
	 STATUS current
	 DESCRIPTION
		 "gslb-protocol"
	::= { portOperEntry 9 }

portOperLocalProtocol OBJECT-TYPE
	 SYNTAX Integer32
	 MAX-ACCESS read-only
	 STATUS current
	 DESCRIPTION
		 "local-protocol"
	::= { portOperEntry 10 }

portOperTcp OBJECT-TYPE
	 SYNTAX Integer32
	 MAX-ACCESS read-only
	 STATUS current
	 DESCRIPTION
		 "tcp"
	::= { portOperEntry 11 }

portOperManuallyHealthCheck OBJECT-TYPE
	 SYNTAX Integer32
	 MAX-ACCESS read-only
	 STATUS current
	 DESCRIPTION
		 "manually-health-check"
	::= { portOperEntry 12 }

portOperUseGslbState OBJECT-TYPE
	 SYNTAX Integer32
	 MAX-ACCESS read-only
	 STATUS current
	 DESCRIPTION
		 "use_gslb_state"
	::= { portOperEntry 13 }

portOperDynamic OBJECT-TYPE
	 SYNTAX Integer32
	 MAX-ACCESS read-only
	 STATUS current
	 DESCRIPTION
		 "dynamic"
	::= { portOperEntry 14 }

END
