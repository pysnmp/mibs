ACOS-FW-TCP-WINDOW-CHECK-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		fwTcpWindowCheckModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "fwTcpWindowCheckModule OID for ACOS"
				::=  {  acosSchema 484 }

tcpWindowCheck		 OBJECT IDENTIFIER ::= { fwTcpWindowCheckModule 1}

tcpWindowCheckStatsTable OBJECT-TYPE
	 SYNTAX SEQUENCE OF TcpWindowCheckStatsEntry
	 MAX-ACCESS not-accessible
	 STATUS current
	 DESCRIPTION
	 "Configure TCP window check from object 'fw.tcp-window-check'"
	::= {tcpWindowCheck 1}

tcpWindowCheckStatsEntry OBJECT-TYPE
	SYNTAX TcpWindowCheckStatsEntry
	MAX-ACCESS not-accessible
	STATUS current
	DESCRIPTION
		"The tcpWindowCheckStats stats entry"
	INDEX {
		tcpWindowCheckStatsSlotId
	}
	::= { tcpWindowCheckStatsTable 1 }

TcpWindowCheckStatsEntry ::=
	SEQUENCE {
		tcpWindowCheckStatsSlotId Integer32,
		tcpWindowCheckStatsOutsideWindow	 CounterBasedGauge64
	}

tcpWindowCheckStatsSlotId OBJECT-TYPE
	 SYNTAX Integer32
	 MAX-ACCESS read-only
	 STATUS current
	 DESCRIPTION
		 ""
	::= { tcpWindowCheckStatsEntry 1 }

tcpWindowCheckStatsOutsideWindow OBJECT-TYPE
	 SYNTAX Integer32
	 MAX-ACCESS read-only
	 STATUS current
	 DESCRIPTION
		 "outside-window"
	::= { tcpWindowCheckStatsEntry 2 }

END
