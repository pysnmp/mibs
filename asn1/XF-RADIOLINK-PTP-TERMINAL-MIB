XF-RADIOLINK-PTP-TERMINAL-MIB DEFINITIONS ::= BEGIN

    IMPORTS
      entPhysicalIndex
        FROM ENTITY-MIB
      entLogicalIndex
        FROM ENTITY-MIB
      ifIndex
        FROM IF-MIB
      PerfCurrentCount, PerfIntervalCount
        FROM PerfHist-TC-MIB
      HCPerfCurrentCount
        FROM HC-PerfHist-TC-MIB
      MODULE-COMPLIANCE, OBJECT-GROUP
        FROM SNMPv2-CONF
      TruthValue, TEXTUAL-CONVENTION
        FROM SNMPv2-TC
      OBJECT-TYPE, MODULE-IDENTITY, TimeTicks, Integer32, Counter32, Counter64, IpAddress
        FROM SNMPv2-SMI
      SnmpAdminString
        FROM SNMP-FRAMEWORK-MIB
      DisplayString
        FROM SNMPv2-TC
      xfRadioLink
        FROM XF-TOP-MIB;

    xfRadioLinkPtpTerminalMIB MODULE-IDENTITY

      LAST-UPDATED "202003170000Z" -- 17 March 2020
      ORGANIZATION
        "Ericsson AB"
      CONTACT-INFO
        "
        Ericsson AB
        BU Networks
        SE-431 84  Molndal
        Sweden
        "
      DESCRIPTION
        "
        This MIB defines objects on terminal level
        for point-to-point Radiolink terminals.
        "
   REVISION "202003170000Z" -- 17 March 2020
        DESCRIPTION
            "
            Rev PBB13
            xfRLPMCurrent15mTable: added the following MOs:
            - xfPMCurrent15mESR
            - xfPMCurrent15mSESR
            - xfPMCurrent15mBBER

            xfRLPMCurrent24hTable: added the following MOs:
            - xfPMCurrent24hESR
            - xfPMCurrent24hSESR
            - xfPMCurrent24hBBER
            "

    REVISION "201912200000Z" -- 20 December 2019
        DESCRIPTION
            "
            Rev PBB12
            Increased upper limit from 135 to 145 dBm and default value adjusted for following MOs:
            - xfExtRFPMSetThreshold15mTLTM
            - xfExtRFPMResetThreshold15mTLTM
            - xfExtRFPMSetThreshold24hTLTM
            "

    REVISION "201911260000Z" -- 26 November 2019
        DESCRIPTION
            "
            Rev PBB11
            Increased upper limit from 35 to 45 dBm for following MOs:
            - xfExtRFPMTLTS1Threshold
            - xfExtRFPMCurrent24hTLMin
            - xfExtRFPMCurrent24hTLMax
            - xfExtRFPMInterval24hTLMin
            - xfExtRFPMInterval24hTLMax
            - xfExtRFPMCurrent15mTLMin
            - xfExtRFPMCurrent15mTLMax
            - xfExtRFPMInterval15mTLMin
            - xfExtRFPMInterval15mTLMax
            "

    REVISION "201805230000Z" -- 23 May 2018
        DESCRIPTION
            "
            Rev PBB10
            Revert change of maximum and default values for Extended PM Thresholds
            in following tables:
            - xfRLExtRFPMConfigTable
            - xfRLExtRFPMCurrent24hTable
            - xfRLExtRFPMInterval24hTable
            - xfRLExtRFPMCurrent15mTable
            - xfRLExtRFPMInterval15mTable
            "

    REVISION "201804270000Z" -- 27 April 2018
        DESCRIPTION
            "
            Rev PBB9
            Updated maximum values of xfPMTLTS1Thresholds.
            "

    REVISION "201804060000Z" -- 6 April 2018
        DESCRIPTION
            "
            Rev PBB8
            Updated unit of measurement of XPI level in performance monitoring counters:
            from dBm to dB.
            "

    REVISION "201709190000Z" -- 19 September 2017
        DESCRIPTION
            "
            Rev PBB7
            - Type of MOs xfPMCurrent24hBBEs/xfPMInterval24hBBEs and xfPMCurrent24hBBs/xfPMInterval24hBBs
              changed to HCPerfCurrentCount.
            - Updated description of MO xfPMSetThreshold15mBBEs: 9000 -> 9900.
            "

    REVISION "201705240000Z" -- 24 May 2017
        DESCRIPTION
            "
            Rev PBB6
            Introduction of new FF 60 MHz.
            "

    REVISION "201610240000Z" -- 24 October 2016
        DESCRIPTION
            "
            Rev PBB5
            New objects in xfRLPtpTerminalXTable:
            xfTermPacketMaxCapacity and xfTermPacketMinCapacity.
            "

    REVISION "201605110000Z" -- 11 May 2016
        DESCRIPTION
            "
            Rev PBB4
            - 'xfTermSpectrumEfficiencyClassObsolete' MO moved to obsolete conformance group.
            "

    REVISION "201605100000Z" -- 10 May 2016
        DESCRIPTION
            "
            Rev PBB3
            - 'Obsolete' MOs set back to 'current' status
              in order to remove warnings.
            "

    REVISION "201602220000Z" -- 22 February 2016
        DESCRIPTION
            "
            Rev PBB2
            - Description updated for some MOs.
            - Readability improvements (formatting).
            "

    REVISION "201602050000Z" -- 5 February 2016
        DESCRIPTION
            "
            Rev PBB1
            - Added tables:
              * xfRLExtRFPMConfigTable
              * xfRLExtRFPMCurrent24hTable
              * xfRLExtRFPMInterval24hTable
              * xfRLExtRFPMCurrent15mTable
              * xfRLExtRFPMInterval15mTable
              * xfRLExtRAUPMCurrent24hTable
              * xfRLExtRAUPMInterval24hTable
              * xfRLExtRAUPMCurrent15mTable
              * xfRLExtRAUPMInterval15mTable
            - Obsoleted the following MOs in xfRLPMConfigTable:
              * xfPMRLTS1Threshold
              * xfPMSetThreshold15mRLTS1
              * xfPMResetThreshold15mRLTS1
              * xfPMRLTS2Threshold
              * xfPMSetThreshold15mRLTS2
              * xfPMResetThreshold15mRLTS2
              * xfPMSetThreshold15mRLTM
              * xfPMResetThreshold15mRLTM
              * xfPMTLTS1Threshold
              * xfPMSetThreshold15mTLTS1
              * xfPMResetThreshold15mTLTS1
              * xfPMSetThreshold15mTLTM
              * xfPMResetThreshold15mTLTM
              * xfPMSetThreshold24hRLTS1
              * xfPMSetThreshold24hRLTS2
              * xfPMSetThreshold24hRLTM
              * xfPMSetThreshold24hTLTS1
              * xfPMSetThreshold24hTLTM
            "

    REVISION "201506080000Z" -- 8 June 2015
        DESCRIPTION
            "
            Rev PBA6
            Updated description text for the following MOs:
                    xfPMSetThreshold15mRLTM,     xfPMResetThreshold15mRLTM,
                    xfPMSetThreshold24hRLTM,     xfPMSetThreshold15mTLTM,
                    xfPMResetThreshold15mTLTM,   xfPMSetThreshold24hTLTM,
                    xfPMCurrent24hMSEMin,        xfPMCurrent24hMSEMax,
                    xfPMInterval24hMSEMin,       xfPMInterval24hMSEMax,
                    xfPMCurrent15mMSEMin,        xfPMCurrent15mMSEMax,
                    xfPMInterval15mMSEMin,       xfPMInterval15mMSEMax
            "

    REVISION "201502260000Z" -- 26 February 2015
        DESCRIPTION
            "
            Rev PBA5
            Add new MIBs for improved power monitoring
            Table xfRLPMConfigTable new MOs:
                    xfPMRLTS1Threshold,          xfPMSetThreshold15mRLTS1,
                    xfPMResetThreshold15mRLTS1,  xfPMRLTS2Threshold,
                    xfPMSetThreshold15mRLTS2,    xfPMResetThreshold15mRLTS2,
                    xfPMSetThreshold15mRLTM,     xfPMResetThreshold15mRLTM,
                    xfPMTLTS1Threshold,          xfPMSetThreshold15mTLTS1,
                    xfPMResetThreshold15mTLTS1,  xfPMSetThreshold15mTLTM,
                    xfPMResetThreshold15mTLTM,   xfPMSetThreshold24hRLTS1,
                    xfPMSetThreshold24hRLTS2,    xfPMSetThreshold24hRLTM,
                    xfPMSetThreshold24hTLTS1,    xfPMSetThreshold24hTLTM
            Table xfRLPMCurrent24hTable new MOs:
                    xfPMCurrent24hRLTS1,         xfPMCurrent24hRLTS2,
                    xfPMCurrent24hRLMin,         xfPMCurrent24hRLMax,
                    xfPMCurrent24hTLTS1,         xfPMCurrent24hTLMin,
                    xfPMCurrent24hTLMax,         xfPMCurrent24hMSEMin,
                    xfPMCurrent24hMSEMax,        xfPMCurrent24hXPIMin,
                    xfPMCurrent24hXPIMax
            Table xfRLPMInterval24hTable New MOs:
                    xfPMInterval24hRLTS1,        xfPMInterval24hRLTS2,
                    xfPMInterval24hRLMin,        xfPMInterval24hRLMax,
                    xfPMInterval24hTLTS1,        xfPMInterval24hTLMin,
                    xfPMInterval24hTLMax,        xfPMInterval24hMSEMin,
                    xfPMInterval24hMSEMax,       xfPMInterval24hXPIMin,
                    xfPMInterval24hXPIMax
            Table xfRLPMCurrent15mTable new MOs:
                    xfPMCurrent15mRLTS1,         xfPMCurrent15mRLTS2,
                    xfPMCurrent15mRLMin,         xfPMCurrent15mRLMax,
                    xfPMCurrent15mTLTS1,         xfPMCurrent15mTLMin,
                    xfPMCurrent15mTLMax,         xfPMCurrent15mMSEMin,
                    xfPMCurrent15mMSEMax,        xfPMCurrent15mXPIMin,
                    xfPMCurrent15mXPIMax
            Table xfRLPMInterval15mTable new MOs:
                    xfPMInterval15mRLTS1,        xfPMInterval15mRLTS2,
                    xfPMInterval15mRLMin,        xfPMInterval15mRLMax,
                    xfPMInterval15mTLTS1,        xfPMInterval15mTLMin,
                    xfPMInterval15mTLMax,        xfPMInterval15mMSEMin,
                    xfPMInterval15mMSEMax,       xfPMInterval15mXPIMin,
                    xfPMInterval15mXPIMax
            "

    REVISION "201407070000Z" -- 7 July 2014
        DESCRIPTION
            "
            Rev PBA4
            Comments adjusted.
            "

    REVISION "201402200000Z" -- 20 Febuary 2014
        DESCRIPTION
            "
            Rev PBA3
            Added SDC Performance tables:
            - xfRLPMSDCGainCurrent15mTable
            - xfRLPMSDCGainInterval15mTable
            - xfRLPMSDCGainCurrent24hTable
            - xfRLPMSDCGainInterval24hTable
            - xfRLPMSDCGainConfigTable
            "

    REVISION "201401150000Z" -- 15 January 2014
        DESCRIPTION
            "
            Rev PBA2
            xfTermChannelModeCapability object extended with values:
            - ccdp16QAM(3)
            - ccdp64QAM(4)
            - ccdp128QAM(5)
            "

    REVISION "201311220000Z" -- 22 November 2013
        DESCRIPTION
            "
            Rev PBA1
            Minor changes for removal of warnings.
            "

    REVISION "201311191400Z" -- 19 November 2013
        DESCRIPTION
            "
            Rev AZ
            Official R-State for M14A
            "

    REVISION "201309250000Z" -- 25 September 2013
        DESCRIPTION
            "Fixed error in xfRLPtpTerminalXTable definition"

    REVISION "201309160000Z" -- 16 September 2013
       DESCRIPTION
            "Remoed objects in xfRLPtpTerminalXTable:
            xfTermXpicStatus, xfTermXpiLevel, xfTermMSELevel"

    REVISION "201307060000Z" -- 06 July 2013
        DESCRIPTION
            "New objects in xfRLPtpTerminalXTable:
            xfTermXpicStatus, xfTermXpiLevel, xfTermMSELevel"

    REVISION "201303280000Z" -- 28 March 2013
        DESCRIPTION
            "
            Rev PAV1
            New objects in xfRLPtpTerminalXTable:
            xfTermConfiguredBitPipeCapacity and xfTermTribCapacityConfigured"

    REVISION "201210260000Z" -- 26 October 2012
        DESCRIPTION
            "
            Rev PAY2
            * New values for XfRLPMAMCurrent15mTable:  xfPMAMCurrent15m4QAMEnRLB  -> xfPMAMCurrent15m1024QAMEnRLB
            * New values for xfRLPMAMCurrent24hTable:  xfPMAMCurrent24h4QAMEnRLB  -> xfPMAMCurrent24h1024QAMEnRLB
            * New values for XfRLPMAMInterval15mTable: xfPMAMInterval15m4QAMEnRLB -> xfPMAMInterval15m1024QAMEnRLB
            * New values for XfRLPMAMInterval24hTable: xfPMAMInterval24h4QAMEnRLB -> xfPMAMInterval24h1024QAMEnRLB
            * New value  for xfRLPtpTerminalPerformanceTable: xfTermTimeElapsedEnRLBExt
            "

    REVISION "201208010000Z" -- 01 August 2012
        DESCRIPTION
            "
            Rev PAF3
            * New value for xfTermProtection: enhancedRLB.
            * New values of xfRLProtectionMode: enhancedRLBProtected and enhancedRLBExtended.
            * New values for xfTermProtectionCapability: nplus1 and enhancedRLB.
            "

    REVISION "201206240000Z" -- 24 June 2012
        DESCRIPTION
            "
            Rev PAF2
            * pdhToTdmAndSDHToSFPHAndSDHToPtP added to xfTermInterfaces
            * Adjusted values in xfTermBerAlarmThresholdCapability
            "

    REVISION "201205290000Z" -- 29 May 2012
        DESCRIPTION
            "
            Rev PAF1
            Added xfTermBerAlarmThresholdCapability
            "

    REVISION "201112160000Z" -- 16 December 2011
        DESCRIPTION
            "
            Rev AE
            Changed to full revision
            "

    REVISION "201112040000Z" -- 04 December 2011
        DESCRIPTION
            "
            Rev PAE3
            Change name of mcOneStm1OneDS1LH
            to oneStm1OneDS1LH
            "

    REVISION "201111220000Z" -- 22 November 2011
        DESCRIPTION
            "
            Rev PAE2
            New capacity value, mcOneStm1OneDS1LH(26)
            New capacity value, mcOneStm1OneDS1LH(25)
            to terminalcapacitycapability array
            "

    REVISION "201111170000Z" -- 17 November 2011
        DESCRIPTION
            "
            Rev PAE1
            Added fftAdmodStatic(10), fftXpicAdmodStatic(11),
            fftAdmodStaticLH(12) and fftXpicAdmodStaticLH(13)
            to xfTermFrameFormatType
            "

    REVISION "201111150000Z" -- 15 November 2011
        DESCRIPTION
            "
            Rev AD
            Updated to an official revision
            "

    REVISION "201109090000Z" -- 9 Sept 2011
        DESCRIPTION
            "
            Rev PAD4
            Added vr150(13), vr250(14), vr300(15),
            vr400(16) and vr450(17) license
            "

    REVISION "201107080000Z" -- 8 July 2011
        DESCRIPTION
            "
            Rev PAD3
            New capacity value, oneStm1OneE1LH(24)
            to terminalcapacitycapability array
            "

    REVISION "201106270000Z" -- 27 June 2011
      DESCRIPTION
          "
          Rev PAD2
          New capacity value, oneStm1OneE1LH(25)
          "

    REVISION "201106010000Z" -- 1 June 2011
      DESCRIPTION
          "
          Rev PAD1
          Changes for TN 5.0.
          New objects in xfRLPtpTerminalXTable:
           xfTermFadingRates and xfTermFadingRatesCapability.
          "

    REVISION "201105230000Z" -- 23 May 2011
      DESCRIPTION
          "
          Rev AC
          Official R-state for TN 4.4 FP
          "

    REVISION "201103040000Z" -- 4 march 2011
      DESCRIPTION
          "
          Rev PAC11
          Changes for Mini Link LH 1.0.
          Added fftStaticLH(6), fftAdmodLH(7),
                fftXpicLH(8) andfftXpicAdmodLH(9)to xfTermFrameFormatType
          "

    REVISION "201102090000Z" -- 9 February 2011
      DESCRIPTION
          "
          Rev PAC10
          Changes for TN 4.4FP.
          Added capability-bit terminalCapacityLicense(3) to
          MO xfTermCapability in table xfRLPtpTerminalXTable.
          "

    REVISION "201102010000Z" -- 1 February 2011
      DESCRIPTION
          "
          Rev PAC9
          Changes for TN 4.4FP.
          Correction for 1024QAM.
          "

    REVISION "201101100000Z" -- 10 January 2011
      DESCRIPTION
          "
          Rev PAC8
          Changes for TN 4.4FP.
          Added MO xfTermCapacityLicense to
          xfRLPtpTerminalXTable.
          Added table xfRLPtpTerminalCapacityLicenseTable
          and it's MOs xfTermCapacityLicenseRange
          xfTermMaxCapacityRange and xfTermMaxTribCapacityRange
          "

    REVISION "201012210000Z" -- 21 December 2010
      DESCRIPTION
          "
          Rev PAC7
          Changes for TN 4.4FP.
          Added capability-bit txSwitchOverConfiguration to
          MO xfRLProtectionCapability in table xfRLProtection.

          Changed MO name from xfTermAdaptiveCapability to xfTermCapability
          and changed the BITS name changing the supports-prefix to a adaptive-prefix
          and added fragmentedTributaries.
          "

    REVISION "201012160000Z" -- 16 December 2010
      DESCRIPTION
          "
          Rev PAC6
          Changes for TN 4.4FP.
          Changed MO-name from xfRLRemoteTxSwitchOverConfiguration to xfRLTxSwitchOverConfiguration.
          "

    REVISION "201012140000Z" -- 14 December 2010
      DESCRIPTION
          "
          Rev PAC5
          Added Describtion for TermAutoRemoveLoopEnable
          Changed name on supportsAtpcFallbackWithAutoRestore
          to supportsAtpcFallbackTimer.
          Added Describtion for xfTermAdaptiveManualMode
          "

    REVISION "201012130000Z" -- 13 December 2010
      DESCRIPTION
          "
          Rev PAC4
          Changes for TN 4.4FP.
          Added 1024QAM.
          "

    REVISION "201011230000Z" -- 23 November 2010
      DESCRIPTION
          "
          Rev PAC3
          Changes for TN 4.4FP.
          Added xfRLRemoteTxSwitchOverConfiguration to xfRLProtectionTable.
          "

    REVISION "201010250000Z" -- 25 October 2010
      DESCRIPTION
          "
          Rev PAC2
          Changes for TN 4.4FP.
          Added xfTermCapability(22) to
          xfRlPtpTerminalXTable and enabledAsRequest(4) to
          xfTermAdaptiveManualMode(13)
          "

    REVISION "201010210000Z" -- 21 October 2010
      DESCRIPTION
          "
          Rev PAC1
          Added supportsAtpcFallbackWithAutoRestore to xfTermAtpcCapability.
          "

    REVISION "201009130000Z" -- 13 September 2010
      DESCRIPTION
          "
          Rev AB
          Changes for TN 4.4.
          Added xfTermAutoRemoveLoopEnable(21) to
          xfRlPtpTerminalXTable.
          "

    REVISION "201009020000Z" -- 2 September 2010
      DESCRIPTION
          "
          Rev PAB4
          Changes for TN 4.4.
          Added xfTermTribAllocationActual(19) and xfTermTribAllocationDesired(20) to
          xfRlPtpTerminalXTable.
          "

    REVISION "201008200000Z" -- 20 Augusti 2010
      DESCRIPTION
          "
          Rev PAB3
          Changes for TN 4.4.
          Added xfRLProtectionCapability(7) to xfRLProtectionTable.
          "

    REVISION "201006150000Z" -- 15 Juni 2010
      DESCRIPTION
          "
          Rev PAB2
          Added UnprotectedSD xfTermProtection and xfRLProtectionTable
          Added TermProtectionCapbility and TermLineProtectionCapability
          to XfRLPtpTerminalXEntry and xfRadioLinkPtpTerminalCompleteGroup
          "

    REVISION "201006040000Z" -- 4 Juni 2010
      DESCRIPTION
          "
          Rev PAB
          Added rlXfMLTNPT(6) to xfTermType
          "

    REVISION "201005270000Z" -- 27 Maj 2010
      DESCRIPTION
          "
          Rev AA
          Added vr500 license
          "

    REVISION "201001190000Z" -- 19 January 20010
      DESCRIPTION
          "
          Rev Z
          Official R-State for TN 4.3
          "

    REVISION "200911180000Z" -- 18 november 2009
      DESCRIPTION
          "
          Rev PZ2
          Added supportsAtpcFallback to xfTermAtpcCapability.
          "

    REVISION "200909180000Z" -- 18 september 2009
      DESCRIPTION
          "
          Rev PZ
          Added xfTermIpAddress to xfRLPtpTerminalXTable.
          "

    REVISION "200906260000Z" -- 26 june 2009
      DESCRIPTION
          "
          Rev Y
          Updated revision history.
          "

    REVISION "200906240000Z" -- 24 june 2009
      DESCRIPTION
          "
          Rev Y
          Official R-State for  TN 4.2
          "

      REVISION "200904140000Z" -- 14 april 2009
      DESCRIPTION
          "
          Rev PX11
          Changes for TN 4.2
          Spectrum Effeciency Class index values have changed.
          Adde new Spectrum Effeciency Class/Capability values.
          Added channelspacing chsp3500kHz(10).
          Added validrow vr4(11).
          "

      REVISION "200903110000Z" -- 11 mars 2009
      DESCRIPTION
          "
          Corrected bit fields for pmamconfig table.
          "

      REVISION "200903040000Z" -- 4 mars 2009
      DESCRIPTION
          "
          Rev X
          This is the same version as Rev PX9, with the changes below:
          Changed name on fftAdaptive to fftAdMod.
          "

      REVISION "200902020000Z" -- 2 feb 2009
      DESCRIPTION
          "
          Rev PX10
          Added new tables:
          - XfRLPMAMConfigTable
          - XfRLPMAMInterval24hTable
          - XfRLPMAMInterval15mTable
          - XfRLPMAMCurrent24hTable
          - XfRLPMAMCurrent15mTable
          New type TermAdaptiveManualMode,
          changed type xfTermAdaptiveManualMode.
          "

      REVISION "200901050000Z" -- 5 jan 2009
      DESCRIPTION
          "
          Rev PX9
          Fixed double index for xfRLPMInterval15mTable
          "

      REVISION "200812040000Z" -- 04 december 2008
      DESCRIPTION
          "
          Rev PX8
          Changes for TN 4.1/4.2
          xfTermBitPipeCapacity description changed from Mbit to Kbit (TR: TTNTR00022525).
          "

      REVISION "200810020000Z" -- 02 october 2008
      DESCRIPTION
          "
          Rev PX7
          Changes for TN 4.1/4.2
          Removed objects in xfRLPtpTerminalXTable: xfTermAdaptiveModulation
          Changed objects in xfRLPtpTerminalXTable:
          - from xfTermManualRowIndex to xfTermAdaptiveManualRowIndex
          - from xfTermDCNHCapacity to xfTermDCNCapacity
          Fixed double index issue in xfRLPtpTerminalXTable
          "

      REVISION "200809160000Z" -- 16 september 2008
      DESCRIPTION
          "
          Rev PX6
          Changes for TN 4.1
          New objects in xfRLPtpTerminalXTable:
          - xfTermActualRowIndex
          - xfTermMaxRowIndex
          - xfTermAdaptiveModulation
          - xfTermManualRowIndex
          - xfTermAdaptiveManualMode
          "

      REVISION "200808150000Z" -- 15 august 2008
      DESCRIPTION
          "
          Rev PX5
          Added rlXfMLStandalone(5) for xfTermTypes in xfRLPtpTerminalTable.
          Fixed wrong values in xfTermFrameFormatRev for xfRlPtpTerminalCapabilityTable.
          "

            REVISION "200806250000Z" -- 25 june 2008
      DESCRIPTION
          "
          Rev PX4
          Changes for TN 4.1
          Changes in table: xfRlPtpTerminalCapabilityTable
          "

      REVISION "200806240000Z" -- 24 june 2008
      DESCRIPTION
          "
          Rev PX3
          Changes for TN 4.1
          Changes in table: xfRlPtpTerminalCapabilityTable (xfTermChannelModulation)
          "

      REVISION "200806180000Z" -- 18 june 2008
      DESCRIPTION
          "
          Rev PX2
          Changes for TN 4.1
          Changes in table: xfRlPtpTerminalCapabilityTable
          "

      REVISION "200806040000Z" -- 4 june 2008
      DESCRIPTION
          "
          Rev PX1
          Changes for TN 4.1
           New objects in xfRLPtpTerminalXTable:
             xfTermTribCapacityActual
             xfTermTribCapacityDesired
             xfTermBitPipeCapacity
             xfTermRowIndex

           New table:
             xfRlPtpTerminalCapabilityTable
          "

      REVISION "200806030000Z" -- 3 june 2008
      DESCRIPTION
          "
          Rev V
          Ordinary revision. No other changes.
          "

      REVISION "200804090000Z" -- 9 april 2008
      DESCRIPTION
          "
          Rev PV5
          Changes for TN4.0:
            Default value descriptions for xfTermCapacity and xfTermModulation corrected.
          "

      REVISION "200803030000Z" -- 3 mar 2008
      DESCRIPTION
          "
          Rev PV3/PV4
          Changes for TN4.0:
            xfTermCapacity and ...Capability extended with two new values: sixtynineDS1 and eightyDS1
            xfRLPtpTerminalXTable added - with these MO's:
               xfTermInterfaces
               xfTermInterfacesCapability
               xfTermChannelModeOperStatus (PV4)
               xfTermXPICRestore (PV4)
          "

      REVISION "200710240000Z" -- 24 oct 2007
      DESCRIPTION
          "
          Rev U
          Ordinary revision for TN 3.3,
          according to  1/155 19-CRH 109 625/1 Uae Rev V
          "

      REVISION "200708140000Z" -- 14 aug 2007
      DESCRIPTION
          "
          Rev PU4
          CR1045: New capacity value, oneStm1OneJ1(22)
          "

      REVISION "200707050000Z" -- 5 july 2007
      DESCRIPTION
          "
          Rev PU3
          Correction: xfPMInterval24hUASs and xfPMInterval24hBBs shall be read-only
          "

      REVISION "200707030000Z" -- 3 july 2007
      DESCRIPTION
          "
          Rev PU2
          New values for xfTermCapacity:
            twentytwoE1(18),
            thirtyfiveE1(19),
            fortysixE1(20),
            seventyfiveE1(21)

          New values for xfTermCapacityCapability:
            twentytwoE1(17),
            thirtyfiveE1(18),
            fortysixE1(19),
            seventyfiveE1(20)
          "

      REVISION "200707020000Z" -- 2 july 2007
      DESCRIPTION
          "
          Rev PU1
          Mib file according to IMPLEMENT. PROPOSAL 6/1594-FCP 101 4733 Uen PB5
          New tables:
            xfRLPMConfigTable
            xfRLPMCurrent24hTable
            xfRLPMInterval24hTable
            xfRLPMCurrent15mTable
            xfRLPMInterval15mTable
          "

      REVISION "200706040000Z" -- 4 june 2007
      DESCRIPTION
          "
          Rev T
          Changes according to 1/15519-CRH109625/1 Uae Rev U.
          - xfRLActiveTxRadio: Change in comment regarding relaxed access limitation.
          - xfRLSwitchOverReset: Change in comment regarding relaxed access limitation.
          "

      REVISION "200703160000Z" -- 16 mar 2007
      DESCRIPTION
          "
          Rev S
          - xfTermTimeElapsed:
              Corrected description field acc. to 1/15519-CRH109625/1 Uae Rev S.
          - xfTermDCNRadioCapability:
              Corrected literals, dcnLinexxx --> dcnRadioxxx
          "

      REVISION "200701170000Z" -- 17 jan 2007
      DESCRIPTION
          "
          Rev N
          Changes according to 1/15519-CRH109625/1 Uae Rev S
          - xfTermCapacity: added value oneStm1oneE1at50MHz(17)

          - xfTermCapacityCapability:
              stm0(12) --> oneStm0(12)
              stm1(13) --> oneStm1oneE1(13)
              oneStm1oneDS1(15) added
              oneStm1oneE1at50MHz(16) added

          - xfTermLineProtection:
              singleInterface(3) SI             --> singleInterfaceLowSlot(3) SI low slot
                                                --> singleInterfaceHighSlot(4) SI high slot
              opticalSplitter(4) EEP            --> opticalSplitter(5) EEP
              equipmentAndLineProtection(5) ELP --> equipmentAndLineProtection(6) ELP

          - xfRLLineProtectionMode:
              singleInterface(3)                --> singleInterfaceLowSlot(3)
                                                --> singleInterfaceHighSlot(4)
              opticalSplitter(4)                --> opticalSplitter(5)
              equipmentAndLineProtection(5)     --> equipmentAndLineProtection(6)
          "

      REVISION "200611140000Z" -- November 14
      DESCRIPTION
          "
          Rev M
          Changes according to 1/15519-CRH109625/1 Uae Rev N
          - xfRADIORSTable moved from XF-RADIOLINK-PTP-MODEM-MIB to this mib.
          - xfRADIORSPerformanceTable moved from XF-RADIOLINK-PTP-MODEM-MIB to this mib.
          "

      REVISION "200609200000Z" -- September 20
      DESCRIPTION
          "
          Rev L
          Correction: Adding MO xfRLLineProtectionMode, according to
           1/15519-CRH109625/1 Uae Rev M
          "

      REVISION "200609191310Z" -- September 19, 2006 at 13:10 GMT
      DESCRIPTION
          "
          Rev K.
          Changed object syntax to improve the display in a mib browser.
          Changed description for object xfTermAlarmSeverity according to
          errata for 1/15519-CRH109625/1 Uae Rev M
          "

      REVISION "200609120000Z"
      DESCRIPTION
          "
          Rev PK5.
          Changes according to 1/15519-CRH109625/1 Uae Rev PM1
            New objects in xfRLPtpTerminalTable
          Moved object descriptions to make them visible in a mib browser.
          "

      REVISION "200609050000Z"
      DESCRIPTION
          "
          Rev PK3.
        - Changes according to 1/15519-CRH109625/1 Uae Rev L
        - Changed value in xfTermCapacity:
            oneStm1(14) --> oneStm1oneE1(14)
        - Added value in xfTermCapacity:
            oneStm1oneDS1(16)
        - Added value in xfTermModulation:
            qam64(6)
        - Added value for xfTermModulationCapability:
            qam64(4)
        - Added objects in xfRlPtpTerminalTable to support SDH, license-handling and
          frame-format handling:
            xfTermChannelMode
            xfTermChannelModeCapability
            xfTermTrafficAndDCN
            xfTermFrameFormat
            xfTermFrameFormatCapability
        - Changed description regarding relaxed far-end restrictions for these objects:
            xfTermId
            xfTermProtection
            xfTermCapacity
            xfTermModulation
            xfTermRemoteIdCheck
            xfTermRemoteId
            xfTermFadeNotificationTimer
        - Changed description regarding functionality for the object xfTermRestore.
        - Changed description regarding default values for xfTermCapacity and xfTermModulation
          "

      REVISION "200603200000Z"
      DESCRIPTION
          "
          Rev. J.
        - Changes according to 1/15519-CRH109625/1 Uae Rev K
        - Addition of Enum values for TermCapacity, TermCapacityCapability,
                            TermModulation, TermModulationCapability to support ANSI.
        "

      REVISION "200602240000Z"
      DESCRIPTION
          "
          Rev. H.
        - Access restrictions explained in the description field for each MO.
        - Default value declarations in the description fields also includes the numerical value.
          "

      REVISION "200601310000Z"
      DESCRIPTION
          "
          Rev. G.
        - xfTermFadeNotificationTimer is read/write again.
        - New value for xfRLLineProtectionStatus: rfInputThresholdProtection
        - Object name xfEquipmentProtectionTable changed to xfTermEquipmentProtectionIndex
        - xfTermSysName(octet string, read-only) added in xfRlPtpTerminalTable
          "

      REVISION "200503010000Z"
      DESCRIPTION
          "
          Rev. F.
        - Changes according to 1/15519-CRH109625/1 Uae Rev E and corrections:
        - Enum values defined for xfRLProtectionMode in xfRLProtectionTable.
        - MAX-ACCESS for MO xfTermFadeNotificationTimer, in xfRLPtpTerminalTable, corrected to be read-only
        - Sequence-numbers for xfRLPtpTerminalPerformanceTable, xfRLProtectionTable and xfRLLineProtectionTable
          adjusted to maintain compatibility.
          "

      REVISION "200412130000Z"
      DESCRIPTION
          "
          Rev. E
        - Changes according to 1/15519-CRH109625/1 Uae Rev D and trouble report HF38086 (see below)
        - XfRLPtpTerminalEntry changed:
          -- xfTermFarEndTxOn removed.
          -- xfTermFadeNotificationTimer and xfEquipmentProtectionTable added
        - Syntax for xfTermTrapEnable changed.
        - xfRLPtpTerminalSwitchIfTable removed
        - xfRLProtectionTable added
        - xfRLLineProtectionTable added
        - xfRadioLinkPtpTerminalCompleteGroup updated according to other changes.
        - values for xfRLActiveTxRadio changed according to trouble report HF38086
        - DEFVAL removed. Default value info declared in corresponding description fields.
          "

       REVISION "200407020000Z"
       DESCRIPTION
          "
          Rev. D
            - All ConfigAlarms are removed
            - xfTermFarEndTxOn MO is added
          "

      REVISION "200406220000Z"
      DESCRIPTION
          "
          Rev. C
            - New coding of xfTermAsPort
          "

      REVISION "200406160000Z"
      DESCRIPTION
          "
          Rev. B
            - All config alarms are defined
            - Alarms are updated with new names
            - xfTermCurrentBBE now of Counter64 type
          "

      REVISION "200405250000Z"
      DESCRIPTION
          "
          Rev. PB2
            - Some minor changes
          "

      REVISION "200405171000Z"
      DESCRIPTION
          "
          Rev. PB1
          - Contact info updated with new contact person.
          - xfTermSynchRemote, xfTermAlarm are removed.
          - Management objects for restore, trap, remote Id check,
          and preset are added.
          - Some attributes in OutputPowerTable moved to RF level.
          - xfTermCurrentAT removed.
          "

      REVISION "200401201000Z"
      DESCRIPTION
        "
        Rev. A    This revision has Integer limits added.
            New xfTermAsPort object in xfRLPtpTerminalTable
            added.
        "

      REVISION "200312171000Z"
      DESCRIPTION
        "
        Rev. PA1    Initial revision
        "

      ::= { xfRadioLink 1 }

--
-- Textual conventions
--

    TermAdaptiveManualMode ::= TEXTUAL-CONVENTION
        STATUS current
        DESCRIPTION
        "Adaptive Modulation mode"
        SYNTAX INTEGER
        {
            other(1),
            disable(2),
            enable(3),
            enabledAsRequest(4)
        }

    TermModulation ::= TEXTUAL-CONVENTION
        STATUS current
        DESCRIPTION
        "Channel Modulation"
        SYNTAX INTEGER
        {
            other(1),
            cqpsk(2),
            qam16(3),
            qam128(4),
            qam32(5),
            qam64(6),
            qam4(7),
            qam8(8),
            qam256(9),
            qam512(10),
            qam1024(11)
        }

    TermOutputPowerStatus ::= TEXTUAL-CONVENTION
        STATUS current
        DESCRIPTION
        "Output power mode"
        SYNTAX INTEGER
        {
            other(1),
            rtpc(2),
            atpc(3),
            localControl(4),
            ra1LocalControlRa2Rtpc(5),
            ra1RtpcRa2LocalControl(6)
        }

    ChannelMode ::= TEXTUAL-CONVENTION
        STATUS current
        DESCRIPTION
        "Terminal channel mode"
        SYNTAX INTEGER
        {
            other(1),
            ccdp(2),
            accp(3),
            acap(4)
        }

    TermRauSec ::= TEXTUAL-CONVENTION
        STATUS current
        DESCRIPTION
        "Spectrum Effeciency Class"
        SYNTAX INTEGER
        {
            other(0),
            sec2(1),
            sec4(2),
            sec5b(3)
        }

    TermAutoRemoveLoopEnable ::= TEXTUAL-CONVENTION
        STATUS current
        DESCRIPTION
        "Auto Removal loops"
        SYNTAX INTEGER
        {
            other(1),
            enable(2),
            disable(3)
        }

--
-- Node definitions
--
    xfRadioLinkPtpTerminalObjects OBJECT IDENTIFIER
        ::= { xfRadioLinkPtpTerminalMIB 1 }
    xfRadioLinkPtpTerminalConformance OBJECT IDENTIFIER
        ::= { xfRadioLinkPtpTerminalMIB 2 }

------------------------------------------------------------------------------
-- xfRLPtpTerminalTable
------------------------------------------------------------------------------
  xfRLPtpTerminalTable OBJECT-TYPE
    SYNTAX SEQUENCE OF XfRLPtpTerminalEntry
    MAX-ACCESS not-accessible
    STATUS current
    DESCRIPTION
      "
      Table for Radiolink point-to-point terminal managed objects.
      The table is indexed with entLogicalIndex.
      "
    ::= { xfRadioLinkPtpTerminalObjects 1 }

  xfRLPtpTerminalEntry OBJECT-TYPE
    SYNTAX XfRLPtpTerminalEntry
    MAX-ACCESS not-accessible
    STATUS current
    DESCRIPTION
      "An entry in the xfRLPtpTerminalTable"
    INDEX { entLogicalIndex}
    ::= { xfRLPtpTerminalTable 1 }

  XfRLPtpTerminalEntry ::=
    SEQUENCE
    {
      xfTermId                    SnmpAdminString,
      xfTermType                  INTEGER,
      xfTermProtection            INTEGER,
      xfTermCapacity              INTEGER,
      xfTermCapacityCapability    BITS,
      xfTermModulation            TermModulation,
      xfTermModulationCapability  BITS,
      xfTermRestore               INTEGER,
      xfTermAlarmSeverity         BITS,
      xfTermTrapEnable            INTEGER,
      xfTermAsPort                INTEGER,
      xfTermRemoteIdCheck         INTEGER,
      xfTermRemoteId              SnmpAdminString,
      xfTermPreset                INTEGER,
      xfTermBerAlarmThreshold     INTEGER,
      xfTermFadeNotificationTimer Integer32,
      xfTermEquipmentProtectionIndex  Integer32,
      xfTermSysName               DisplayString,
      xfTermChannelMode           ChannelMode,
      xfTermChannelModeCapability BITS,
      xfTermTrafficAndDCN         INTEGER,
      xfTermFrameFormat           INTEGER,
      xfTermFrameFormatCapability BITS,
      xfTermDCNRadioConfiguration INTEGER,
      xfTermDCNRadioCapability    BITS,
      xfTermDCNLineConfiguration  INTEGER,
      xfTermDCNLineCapability     BITS,
      xfTermFadeNotificationConfiguration INTEGER,
      xfTermLineProtection        INTEGER
    }

--
-- The xfRLPtpTerminalTable MOs
--

  xfTermId OBJECT-TYPE
    SYNTAX SnmpAdminString (SIZE (4))
    MAX-ACCESS read-write
    STATUS current
    DESCRIPTION
      "
      Network identity for terminal.
      Same as GNM id.
      Note! Id TRMA, TRMB, SMMA, SMMB, AAAA and BBBB are not possible to set.
      Default = .TRMA. (also for Far End)
      Near end access: read-write
      Far end access: read-write (Traffic Node), read-only (other)
      "
    ::= { xfRLPtpTerminalEntry 1 }

  xfTermType OBJECT-TYPE
    SYNTAX INTEGER
    {
      other(1),
      rlMLE(2),
      rlXfMLE(3),
      rlXfMLTN(4),
      rlXfMLStandalone(5),
      rlXfMLTNPT(6)
    }
    MAX-ACCESS read-only
    STATUS current
    DESCRIPTION
      "
      Terminal type
      - other    - Unknown
      - rlMLE    - MLE classic
      - rlXfMLE  - MMU2
      - rlXfMLTN - MMU2B
      - rlXfMLStandalone(5) - MMU2 CS
      - rlXfMLTNPT(6) - Pt1
      "
    ::= { xfRLPtpTerminalEntry 2 }

  xfTermProtection OBJECT-TYPE
    SYNTAX INTEGER
    {
      other(1),
      unprotected(2),
      protectedHotStandby(3),
      protectedWorkingStandby(4),
      unProtectedSDC(5),
      enhancedRLB(6)
    }
    MAX-ACCESS read-write
    STATUS current
    DESCRIPTION
      "
      This object sets the protection mode of the terminal.
      - other                   - Unknown
      - unprotected             - 1+0
      - protectedHotStandby     - 1+1 Hot
      - protectedWorkingStandby - 1+1 Working
      - UnProtectedSDC          - 1+0 with Space Diversity
      - enhancedRLB             - Enhanced Radio Link Bonding (1+1 PDH and 1+1/2+0 Ethernet)
      Default value: unprotected(2)
      Near end access: read-write
      Far end access: read-write (Traffic Node), read-only (other)
      "
    ::= { xfRLPtpTerminalEntry 3 }

  xfTermCapacity OBJECT-TYPE
    SYNTAX INTEGER
    {
      other(1),
      twoE1(2),
      fourE1(3),
      oneE2(4),
      twoE2(5),
      oneE3oneE1(6),
      twoE3(7),
      fourE3(8),
      fourDS1(9),
      eightDS1(10),
      sixteenDS1(11),
      seventeenDS1(12),
      oneStm0(13),
      oneStm1oneE1(14),
      thirtytwoDS1(15),
      oneStm1oneDS1(16),
      oneStm1oneE1at50MHz(17),
      twentytwoE1(18),
      thirtyfiveE1(19),
      fortysixE1(20),
      seventyfiveE1(21),
      oneStm1OneJ1(22),
      sixtynineDS1(23),
      eightyDS1(24),
      oneStm1OneE1LH(25),
      oneStm1OneDS1LH(26)
    }
    MAX-ACCESS read-write
    STATUS current
    DESCRIPTION
      "
      This object sets the capacity on the terminal
      * other        - Unknown
      * twoE1        - 2x2 Mbps
      * fourE1       - 4*2 Mbps (only rlMLE)
      * oneE2        - 8 Mbps
      * twoE2        - 2x8 Mbps
      * oneE3oneE1   - 34+2 Mbps
      * twoE3        - 2x34 Mbps
      * fourE3       - 4*34 Mbps
      * fourDS1      - 4xDS1
      * eightDS1     - 8xDS1
      * sixteenDS1   - 16*DS1
      * seventeenDS1 - 16DS1+DS1
      * oneStm0      - STM-0
      * oneStm1oneE1 - STM-1+2
      * thirtytwoDS1 - 32xDS1
      * oneStm1oneDS1 - STM-1+DS1
      * oneStm1oneE1at50MHz - STM-1+2 Mpbs @ 50 MHz
      * twentytwoE1   - 22xE1
      * thirtyfiveE1  - 35xE1
      * fortysixE1    - 46xE1
      * seventyfiveE1 - 75xE1
      * oneStm1OneJ1  - 1xSTM-1 + 1xJ1
      * sixtynineDS1  - 69xDS1
      * eightyDS1     - 80xDS1
      * oneStm1OneE1LH  - STM-1+2 for LH
      * oneStm1OneDS1LH - STM-1+DS1 for LH

      Default value PDH CQPSK ETSI: twoE1(2)            MMU2, MMU2 B, MMU2 C
      Default value PDH CQPSK ANSI: fourDS1(9)          MMU2 BA, MMU2 CA
      Default value PDH QAM   ETSI: twentytwoE1(18)     MMU2 D
      Default value PDH QAM   ANSI: sixtynineDS1(23)    MMU2 DA
      Default value SDH       ETSI: oneStm1oneE1(14)    MMU2 E, MMU2 F
      Default value SDH       ANSI: oneStm1oneDS1(16)   MMU2 E, MMU2 F

      Near end access: read-write
      Far end access: read-write (Traffic Node), read-only (MLE)

      Note that setting far end xfTermCapacity will remove far end traffic cross connects.

      oneStm1oneE1(14) and oneStm1oneE1at50MHz(17) has
      the same capacity and modulation but at different
      bandwidth, hence the two values.

      Capacities above 2xE1 for MMU2 B OFH, MMU2 C OFH,
      ATU and ATU B OFH are under license control.
      "
    ::= { xfRLPtpTerminalEntry 4 }

  xfTermCapacityCapability OBJECT-TYPE
    SYNTAX BITS
    {
      oneE1(0),
      twoE1(1),
      fourE1(2),
      oneE2(3),
      twoE2(4),
      oneE3oneE1(5),
      twoE3(6),
      fourE3(7),
      fourDS1(8),
      eightDS1(9),
      sixteenDS1(10),
      seventeenDS1(11),
      oneStm0(12),
      oneStm1oneE1(13),
      thirtytwoDS1(14),
      oneStm1oneDS1(15),
      oneStm1oneE1at50MHz(16),
      twentytwoE1(17),
      thirtyfiveE1(18),
      fortysixE1(19),
      seventyfiveE1(20),
      oneStm1OneJ1(21),
      sixtynineDS1(22),
      eightyDS1(23),
      oneStm1OneE1LH(24),
      oneStm1OneDS1LH(25)
    }
    MAX-ACCESS read-only
    STATUS current
    DESCRIPTION
      "
      This object shows the capacity capability on the terminal.
      Binary AND on contained modems units capabilities.
      "
    ::= { xfRLPtpTerminalEntry 5 }

  xfTermModulation OBJECT-TYPE
    SYNTAX TermModulation
    MAX-ACCESS read-write
    STATUS current
    DESCRIPTION
      "
      This object sets the modulation method on the terminal.
      Legal settable values are:
      - cqpsk(2)  CQPSK
      - qam16(3)  16-QAM
      - qam128(4) 128-QAM
      - qam32(5)  32-QAM
      - qam64(6)  64-QAM
      Default value PDH CQPSK ETSI: cqpsk(2)    MMU2, MMU2 B, MMU2 C
      Default value PDH CQPSK ANSI: cqpsk(2)    MMU2 BA, MMU2 CA
      Default value PDH QAM   ETSI: qam16(3)    MMU2 D
      Default value PDH QAM   ANSI: qam128(4)   MMU2 DA
      Default value SDH       ETSI: qam128(4)   MMU2 E, MMU2 F
      Default value SDH       ANSI: qam128(4)   MMU2 E, MMU2 F
      Near end access: read-write
      Far end access: read-write (Traffic Node), read-only (other)
      Note that setting far end xfTermModulation might remove far end traffic connections.
      Modulation other than CQPSK for MMU2 C OFH are under license control.
      "
    ::= { xfRLPtpTerminalEntry 6 }

  xfTermModulationCapability OBJECT-TYPE
    SYNTAX BITS
    {
      cqpsk(0),
      qam16(1),
      qam128(2),
      qam32(3),
      qam64(4)
    }
    MAX-ACCESS read-only
    STATUS current
    DESCRIPTION
      "
      This object shows the modulation capability on the terminal.
      Binary AND on contained modems and radio units capabilities.
      "
    ::= { xfRLPtpTerminalEntry 7 }

  xfTermRestore OBJECT-TYPE
    SYNTAX INTEGER { restore(1) }
    MAX-ACCESS read-write
    STATUS current
    DESCRIPTION
      "
      rlXfMLTN:
      Restore command is clearing RF, IF and RxLoop, enable xfTermTrapEnable,
      turn transmitter on and set protection switch mode to Auto.
      In case of MMU2 E and MMU2 F it also clears the STM-1 Line Loop and Local Loop.

      Far end rlMLE and rlXfMLE:
      Restore command sets P-mark to off, all loops are set to off, all Test Port connections
      are removed, Transmitter is set to On and Switch Mode is set to Auto.
      "
    ::= { xfRLPtpTerminalEntry 8 }

  xfTermAlarmSeverity OBJECT-TYPE
    SYNTAX BITS
    {
      termSeverity0(0),
      termSeverity1(1),
      termSeverity2(2)
    }
    MAX-ACCESS read-only
    STATUS current
    DESCRIPTION
      "
      This object shows the highest alarm severity for contained
      units and interfaces in the terminal including E1, E2 and E3 interfaces.
      Terminal alarm severity is indicated by 3 bits:
      bits   012
             000 clear
             001 undetermined
             010 warning
             011 minor
             100 major
             101 critical
             110 not defined
             111 not applicable
      "
    ::= { xfRLPtpTerminalEntry 9 }

  xfTermTrapEnable OBJECT-TYPE
    SYNTAX  INTEGER { unknown(1), enable(2), disable(3) }
    MAX-ACCESS read-write
    STATUS current
    DESCRIPTION
      "
      Disables/enables trap sending from this terminal.
      Note, terminals with termType = rlXfMLE will not include E1, E2 and E3 interfaces.
      Default value: enable(2)
      "
    ::= { xfRLPtpTerminalEntry 10 }

  xfTermAsPort OBJECT-TYPE
    SYNTAX INTEGER
    {
      notAvailable(1),
      aspX002(2),
      aspX003(3),
      aspX004(4),
      aspX005(5),
      aspX006(6),
      aspX007(7),
      aspX008(8),
      aspX009(9),
      aspX010(10),
      aspX011(11),
      aspX012(12),
      aspX013(13),
      aspX014(14),
      aspX015(15),
      aspX016(16),
      aspX017(17),
      aspX018(18),
      aspX019(19),
      aspX020(20),
      aspX021(21)
    }
    MAX-ACCESS read-only
    STATUS current
    DESCRIPTION
      "
      rlXfMLTN: Access server port used to reach far end terminals of type rlMLE or rlXfMLE,
      else notAvailable (1).
      rlXfMLE: Access server port used to reach a near end terminal of type rlXfMLE.
            aspX002      - Port 3002/4002
               ..        - ..
            aspX021      - Port 3021/4021

            Note, Last available port differs between
            different AMMs.
            AMM 2p:  aspX003
            AMM 6p:  aspX006
            AMM 20p: aspX021

      Near end access: read-only
      Far end access: no access
      "
    ::= { xfRLPtpTerminalEntry 11 }

  xfTermRemoteIdCheck OBJECT-TYPE
    SYNTAX INTEGER
    {
      other(1),
      enable(2),
      disable(3)
    }
    MAX-ACCESS read-write
    STATUS current
    DESCRIPTION
      "
      This object sets if check of identity of remote terminal shall be performed or not.
      Legal values are:
      - enable(2): radio id check enabled
      - disable(3): radio id check disabled
      Default value: disable(3)
      "
    ::= { xfRLPtpTerminalEntry 12 }

  xfTermRemoteId OBJECT-TYPE
    SYNTAX SnmpAdminString (SIZE (4))
    MAX-ACCESS read-write
    STATUS current
    DESCRIPTION
      "
      Network identity for remote terminal. Same as GNM id.
      Note: TRMA, TRMB, SMMA, SMMB, AAAA and BBBB are not possible to set.
      A change of the far end value might disconnect IP DCN, but
      internal GNM connection will not be disconnected.
      Default value: TRMB (initial)
      "
    ::= { xfRLPtpTerminalEntry 13 }

  xfTermPreset OBJECT-TYPE
    SYNTAX INTEGER { preset(1) }
    MAX-ACCESS read-write
    STATUS current
    DESCRIPTION
      "
      For terminals with termType = rlXfMLE or rlMLE:
      - Terminal is restored with factory settings.
      - Protected terminals will be set to unprotected.
      For terminals with termType = rlXfMLTN:
      - Terminal is restored with default configuration.

      Near end access: read-write
      Far end access: no access
      "
    ::= { xfRLPtpTerminalEntry 14 }

  xfTermBerAlarmThreshold OBJECT-TYPE
    SYNTAX INTEGER
    {
      other(1),
      ber1e3(2),
      ber1e4(3),
      ber1e5(4),
      ber1e6(5)
    }
    MAX-ACCESS read-write
    STATUS current
    DESCRIPTION
      "
      Threshold for BER alarm.
      Legal values:
      - ber1e3(2): BER=1e-3 (default)
      - ber1e4(3): BER=1e-4
      - ber1e5(4): BER=1e-5
      - ber1e6(5): BER=1e-6
      "
    ::= { xfRLPtpTerminalEntry 15 }

  xfTermFadeNotificationTimer OBJECT-TYPE
    SYNTAX Integer32 (0..1000)
    MAX-ACCESS read-write
    STATUS current
    DESCRIPTION
      "
      Notification suppression timer for protection alarms.
      Unit: 1 sec
      Value range: 0-1000
      Default value: 200
      Near end access: read-write
      Far end access: read-only (Traffic Node)
      "
    ::= { xfRLPtpTerminalEntry 16 }

  xfTermEquipmentProtectionIndex OBJECT-TYPE
    SYNTAX Integer32
    MAX-ACCESS read-only
    STATUS current
    DESCRIPTION
      "
      Unprotected: 0
      Protected: EntPhysicalindex of MMU in lowest slot
      "
    ::= { xfRLPtpTerminalEntry 17 }

  xfTermSysName OBJECT-TYPE
    SYNTAX DisplayString (SIZE (0..255))
    MAX-ACCESS read-only
    STATUS current
    DESCRIPTION
      "
      The system name of the TN hosting the terminal.
      Near end terminal: a zero-length string is returned as MIB-II/system/sysName should be used instead.
      Far end terminal: the system name is returned.
      "
    ::= { xfRLPtpTerminalEntry 18 }

  xfTermChannelMode OBJECT-TYPE
    SYNTAX ChannelMode
    MAX-ACCESS read-write
    STATUS current
    DESCRIPTION
      "
      Channel mode for the terminal (administrative status).
      This is only settable according to xfTermChannelModeCapability.
      Legal values are:
      - ccdp(2): Co-Channel Dual Polarization (XPIC)
      - accp(3): Adjacent Channels Co-Polarization (non-XPIC)
      - acap(4): Adjacent Channels Alternate Polarization (non-XPIC)
      Default value: acap(4)
      Near end access: read-write
      Far end access: read-write (Traffic Node only)
      "
    ::= { xfRLPtpTerminalEntry 19 }

  xfTermChannelModeCapability OBJECT-TYPE
    SYNTAX BITS
    {
      ccdp(0),
      accp(1),
      acap(2),
      ccdp16QAM(3),
      ccdp64QAM(4),
      ccdp128QAM(5)
    }
    MAX-ACCESS read-only
    STATUS current
    DESCRIPTION
      "
      Channel mode capability.
      Legal values are:
      - ccdp(0) ........ Co-Channel Dual Polarization (XPIC)
      - accp(1) ........ Adjacent Channels Co-Polarization (non-XPIC)
      - acap(2) ........ Adjacent Channels Alternate Polarization (non-XPIC)
      - ccdp16QAM(3).... Co-Channel Dual Polarization (XPIC) for 16QAM only on MMU2 F
      - ccdp64QAM(4).... Co-Channel Dual Polarization (XPIC) for 64QAM only on MMU2 F
      - ccdp128QAM(5)... Co-Channel Dual Polarization (XPIC) for 128QAM only on MMU2 F
      Default value: acap(2)
      Near end access: read-write
      Far end access: read-write (Traffic Node only)
      "
    ::= { xfRLPtpTerminalEntry 20 }

  xfTermTrafficAndDCN OBJECT-TYPE
    SYNTAX INTEGER {trafficAndDCN(1), dcnOnly(2)}
    MAX-ACCESS read-write
    STATUS current
    DESCRIPTION
      "
      Enable or disable traffic.
      AIS is generated on all traffic interfaces when traffic is disabled,
      i.e. xfTermTrafficAndDCN = DCNOnly. The hop and DCN is working, though
      (primarily used for license handling).
      Default value: trafficAndDCN(1)
      Near end access: read-write
      Far end access: read-write (Traffic Node only)
      "
    ::= { xfRLPtpTerminalEntry 21 }

  xfTermFrameFormat OBJECT-TYPE
    SYNTAX INTEGER
    {
      other(1),
      version0(2),
      version1(3)
    }
    MAX-ACCESS read-write
    STATUS current
    DESCRIPTION
      "
      The frame format version used by the modem.
      Legal values are:
      - version0(2) only valid for MMU2 C modems
      - version1(3) only valid for MMU2 C modem.
      Default value: other(1)
      Near end access: read-write
      Far end access: read-write (Traffic Node only)
      "
    ::= { xfRLPtpTerminalEntry 22 }

  xfTermFrameFormatCapability OBJECT-TYPE
    SYNTAX BITS
    {
      version0(0),
      version1(1)
    }
    MAX-ACCESS read-only
    STATUS current
    DESCRIPTION
      "
      Frame format versions supported by the modem.
      Bit 0: modem MMU2 C supports frame format Version 0
      Bit 1: modem MMU2 C supports frame format Version 1 (for QAM 2xE2, E3+E1 and 2xE3)
      "
    ::= { xfRLPtpTerminalEntry 23 }

  xfTermDCNRadioConfiguration OBJECT-TYPE
    SYNTAX INTEGER
    {
      other(1),
      dcnRadio128kbps(2),
      dcnRadio320kbpsDCCr(3),
      dcnRadio320kbpsMSB(4)
    }
    MAX-ACCESS read-write
    STATUS current
    DESCRIPTION
      "
      DCN radio capacity for terminal.
      Legal values are:
      - dcnRadio128kbps(2)     RFCOH channel only: all RSOH bytes pass transparently over the hop
      - dcnRadio320kbpsDCCr(3) 128 kbps + DCCr (default)
      - dcnRadio320kbpsMSB (4) 128 kbps + MSB

      Note: Future compatibility is guaranteed if the MSB [(2,2), (3,2), (3,3)]
            are used when 320kbpsMSB value is selected.

      Near end access: read-write
      Far end access: read-write (Traffic Node only)
      "
    ::= { xfRLPtpTerminalEntry 24 }

  xfTermDCNRadioCapability OBJECT-TYPE
    SYNTAX BITS
    {
      dcnRadio128kbps(0),
      dcnRadio320kbpsDCCr(1),
      dcnRadio320kbpsMSB(2)
    }
    MAX-ACCESS read-only
    STATUS current
    DESCRIPTION
      "
      Binary AND on contained MMUs DCN radio configuration capability.
        bits 210
             000 undetermined
             001 128kbps
             010 320kbpsDCCr
             100 320kbpsMSB
             ...
             111 128kbps & 320kbpsDCCr & 320kbpsMSB
      "
    ::= { xfRLPtpTerminalEntry 25 }

  xfTermDCNLineConfiguration OBJECT-TYPE
    SYNTAX INTEGER
    {
      other(1),
      transparent(2),
      dcnLine192kbpsDCCr(3),
      dcnLine192kbpsMSB(4)
    }
    MAX-ACCESS read-write
    STATUS current
    DESCRIPTION
      "
      DCN line capacity for terminal.
      Legal values are:
       transparent(2)        All RSOH bytes pass transparently over the hop.
       dcnLine192kbpsDCCr(3) (default) DCCr
       dcnLine192kbpsMSB(4)  MSB

      Note: Future compatibility is guaranteed if the MSB [(2,2), (3,2), (3,3)]
            are used when 192kbpsMSB value is selected.

      Default value: dcnLine192kbpsDCCr(3)
      Near end access: read-write
      Far end access: read-write (Traffic Node only)
      "
    ::= { xfRLPtpTerminalEntry 26 }

  xfTermDCNLineCapability OBJECT-TYPE
    SYNTAX BITS
    {
      transparent(0),
      dcnLine192kbpsDCCr(1),
      dcnLine192kbpsMSB(2)
    }
    MAX-ACCESS read-only
    STATUS current
    DESCRIPTION
      "
      Binary AND on contained MMUs DCN line configuration.
        bits 210
             000 undetermined
             001 transparent
             010 192kbpsDCCr
             100 192kbpsMSB
             ...
             111 transparent & 192kbpsDCCr & 192kbpsMSB
      "
    ::= { xfRLPtpTerminalEntry 27 }

  xfTermFadeNotificationConfiguration OBJECT-TYPE
    SYNTAX INTEGER
    {
      other(1),
      disabled(2),
      enabled(3)
    }
    MAX-ACCESS read-write
    STATUS current
    DESCRIPTION
      "
      This object enables or disables the notification suppress timer for Protection alarm.
      Default value: enabled(3),
      Near end access: read-write
      Far end access: read-write (Traffic Node only)
      "
    ::= { xfRLPtpTerminalEntry 28 }

  xfTermLineProtection OBJECT-TYPE
    SYNTAX INTEGER
    {
      other(1),
      unProtected(2),
      singleInterfaceLowSlot(3),
      singleInterfaceHighSlot(4),
      opticalSplitter(5),
      equipmentAndLineProtection(6)
    }
    MAX-ACCESS read-write
    STATUS current
    DESCRIPTION
      "
      Administrative status of the line protection for a terminal physical line
      interface, e.g. MMU2 E and MMU2 F. Operational status is xfRLLineProtectionMode.
      Legal values are:
        other(1)      (Not settable)
        unProtected(2)
        singleInterfaceLowSlot(3) SI low slot
        singleInterfaceHighSlot(4) SI high slot
        opticalSplitter(5) EEP
        equipmentAndLineProtection(6). ELP

      Default value: unProtected(2)
      Near end access: read-write
      Far end access: read-write (Traffic Node only)
      "
    ::= { xfRLPtpTerminalEntry 29 }

------------------------------------------------------------------------------
-- xfRLPtpTerminalOutputPowerTable
------------------------------------------------------------------------------
  xfRLPtpTerminalOutputPowerTable OBJECT-TYPE
    SYNTAX SEQUENCE OF XfRLPtpTerminalOutputPowerEntry
    MAX-ACCESS not-accessible
    STATUS current
    DESCRIPTION
      "
      Table for Radiolink point-to-points terminal output power
      managed objects. The tabled is indexed with entLogicalIndex.
      "
    ::= { xfRadioLinkPtpTerminalObjects 2 }

  xfRLPtpTerminalOutputPowerEntry OBJECT-TYPE
    SYNTAX XfRLPtpTerminalOutputPowerEntry
    MAX-ACCESS not-accessible
    STATUS current
    DESCRIPTION
      "An entry in the xfRLPtpTerminalOutputPowerTable"
    INDEX { entLogicalIndex}
    ::= { xfRLPtpTerminalOutputPowerTable 1 }

  XfRLPtpTerminalOutputPowerEntry ::=
    SEQUENCE
    {
      xfTermOutputPowerOperStatus     TermOutputPowerStatus,
      xfTermOutputPowerAdminStatus    TermOutputPowerStatus,
      xfTermAtpcCapability            INTEGER
    }

--
-- The xfRLPtpTerminalOutputPowerTable MOs
--

  xfTermOutputPowerOperStatus OBJECT-TYPE
    SYNTAX TermOutputPowerStatus
    MAX-ACCESS read-only
    STATUS current
    DESCRIPTION
      "
      This object shows the output power mode that is
      running. It is necessarily not equal to configured mode.
      "
    ::= { xfRLPtpTerminalOutputPowerEntry 1 }

  xfTermOutputPowerAdminStatus OBJECT-TYPE
    SYNTAX TermOutputPowerStatus
    MAX-ACCESS read-write
    STATUS current
    DESCRIPTION
      "
      This object sets the output mode of the terminal.
      Legal values are:
      - other(1)
      - rtpc(2)
      - atpc(3)
      - localControl(4)
      - ra1LocalControlRa2Rtpc(5)
      - ra1RtpcRa2LocalControl(6)

      Note, It is only possible to select atpc if
      xfTermAtpcCapability = supportsAtpc for both near end
      and far end terminal. Value other(1) not settable.
      Default value: rtpc(2)
      "
    ::= { xfRLPtpTerminalOutputPowerEntry 2 }

  xfTermAtpcCapability OBJECT-TYPE
    SYNTAX INTEGER
    {
      other(1),
      noAtpcSupport(2),
      doesNotExist(3),
      atpcCapabilityUnknown(4),
      supportsAtpc(5),
      supportsAtpcFallback(6),
      supportsAtpcFallbackTimer(7)
    }
    MAX-ACCESS read-only
    STATUS current
    DESCRIPTION
      "
      This object shows the ATPC capability for the
      terminal, calculated as worst case capability
      for all units contained in the terminal.
      "
    ::= { xfRLPtpTerminalOutputPowerEntry 3 }

------------------------------------------------------------------------------
-- xfRLPtpTerminalPerformanceTable
------------------------------------------------------------------------------
  xfRLPtpTerminalPerformanceTable OBJECT-TYPE
    SYNTAX SEQUENCE OF XfRLPtpTerminalPerformanceEntry
    MAX-ACCESS not-accessible
    STATUS current
    DESCRIPTION
      "
      Table for performance data. For 1+0 systems performance
      data is calculated according to ITU-T Rec. G.826. For
      1+1 systems - calculated as the combined performance
      of the protected terminal.

      1+0 terminals uses ifindex for RAU IF
      1+1 terminals uses ifindex for SWITCH IF
      "
    ::= { xfRadioLinkPtpTerminalObjects  4 }

  xfRLPtpTerminalPerformanceEntry OBJECT-TYPE
    SYNTAX XfRLPtpTerminalPerformanceEntry
    MAX-ACCESS not-accessible
    STATUS current
    DESCRIPTION
      "An entry in the xfRLPtpTerminalPerformanceTable"
    INDEX { ifIndex}
    ::= { xfRLPtpTerminalPerformanceTable 1 }

  XfRLPtpTerminalPerformanceEntry ::=
    SEQUENCE
    {
      xfTermTimeElapsed     Counter32,
      xfTermCurrentES       Counter32,
      xfTermCurrentSES      Counter32,
      xfTermCurrentBBE      Counter64,
      xfTermCurrentUAS      Counter32,
      xfTermCurrentBB       Counter64,
      xfTermPerfReset       INTEGER,
      xfTermTimeElapsedEnRLBExt Counter32
    }

--
-- The xfRLPtpTerminalPerformanceTable MOs
--

  xfTermTimeElapsed OBJECT-TYPE
    SYNTAX Counter32
    MAX-ACCESS read-only
    STATUS current
    DESCRIPTION
      "
      The number of seconds that have elapsed
      since the beginning of the current error-measurement
      period.

      If the current interval exceeds the maximum
      value, the agent will return the maximum
      value.
      "
    ::= { xfRLPtpTerminalPerformanceEntry 1 }

  xfTermCurrentES OBJECT-TYPE
    SYNTAX Counter32
    MAX-ACCESS read-only
    STATUS current
    DESCRIPTION
      "
      This object shows the error seconds.
      "
    ::= { xfRLPtpTerminalPerformanceEntry 2 }

  xfTermCurrentSES OBJECT-TYPE
    SYNTAX Counter32
    MAX-ACCESS read-only
    STATUS current
    DESCRIPTION
      "
      This object shows the severely error seconds.
      "
    ::= { xfRLPtpTerminalPerformanceEntry 3 }

  xfTermCurrentBBE OBJECT-TYPE
    SYNTAX Counter64
    MAX-ACCESS read-only
    STATUS current
    DESCRIPTION
      "
      This object shows the background block errors.
      "
    ::= { xfRLPtpTerminalPerformanceEntry 4 }

  xfTermCurrentUAS OBJECT-TYPE
    SYNTAX Counter32
    MAX-ACCESS read-only
    STATUS current
    DESCRIPTION
      "
      This object shows the unavailable seconds (or unavailable time).
      "
    ::= { xfRLPtpTerminalPerformanceEntry 5 }

  xfTermCurrentBB OBJECT-TYPE
    SYNTAX Counter64
    MAX-ACCESS read-only
    STATUS current
    DESCRIPTION
      "
      This object shows the background blocks.
      "
    ::= { xfRLPtpTerminalPerformanceEntry 6 }

  xfTermPerfReset OBJECT-TYPE
    SYNTAX INTEGER { performanceReset(1) }
    MAX-ACCESS read-write
    STATUS current
    DESCRIPTION
      "
      This object is used to reset the performance counters.
      It is settable also when the radio unit isn't present.
      Near end access: read-write
      Far end access: read-write (Traffic Node only)
      "
    ::= { xfRLPtpTerminalPerformanceEntry 7 }

  xfTermTimeElapsedEnRLBExt OBJECT-TYPE
    SYNTAX Counter32
    MAX-ACCESS read-only
    STATUS current
    DESCRIPTION
      "
      The number of seconds that have elapsed
      in Enhanced RLB Extended capacity mode
      since RLB was enabled and the beginning of
      the current measurement period.
      "
    ::= { xfRLPtpTerminalPerformanceEntry 8 }

------------------------------------------------------------------------------
-- xfRLProtectionTable
------------------------------------------------------------------------------
  xfRLProtectionTable OBJECT-TYPE
    SYNTAX SEQUENCE OF XfRLProtectionEntry
    MAX-ACCESS not-accessible
    STATUS current
    DESCRIPTION
      "
      Table for control and supervision of the protection mechanism
      "
    ::= { xfRadioLinkPtpTerminalObjects  5 }

  xfRLProtectionEntry OBJECT-TYPE
    SYNTAX XfRLProtectionEntry
    MAX-ACCESS not-accessible
    STATUS current
    DESCRIPTION
      "An entry in the xfRLProtectionTable"
    INDEX { entPhysicalIndex }
    ::= { xfRLProtectionTable 1 }

  XfRLProtectionEntry ::=
    SEQUENCE
    {
      xfRLProtectionMode    INTEGER,
      xfRLProtectionRau1    Integer32,
      xfRLProtectionRau2    Integer32,
      xfRLActiveTxRadio   INTEGER,
      xfRLSwitchOverReset   INTEGER,
      xfRLSwitchRevertiveTx   INTEGER,
      xfRLProtectionCapability    BITS,
      xfRLTxSwitchOverConfiguration  INTEGER
    }

--
-- The xfRLProtectionTable MOs
--

  xfRLProtectionMode OBJECT-TYPE
    SYNTAX INTEGER
    {
      other(1),
      unprotected(2),
      protectedHotStandby(3),
      protectedWorkingStandby(4),
      unProtectedSDC(5),
      enhancedRLBProtected(7),
      enhancedRLBExtended(8)
    }
    MAX-ACCESS read-only
    STATUS current
    DESCRIPTION
      "
      This is the operational status of the protection mode.
      Default: unprotected(2)
      "
    ::= { xfRLProtectionEntry 1 }

  xfRLProtectionRau1 OBJECT-TYPE
    SYNTAX Integer32
    MAX-ACCESS read-only
    STATUS current
    DESCRIPTION
      "
      entPhysicalIndex for RAU 1.
      "
    ::= { xfRLProtectionEntry 2 }

  xfRLProtectionRau2 OBJECT-TYPE
    SYNTAX Integer32
    MAX-ACCESS read-only
    STATUS current
    DESCRIPTION
      "
      entPhysicalIndex for RAU 2.
      "
    ::= { xfRLProtectionEntry 3 }

  xfRLActiveTxRadio OBJECT-TYPE
    SYNTAX INTEGER { txRadio1(1), txRadio2(2), txRadio1andtxRadio2(3) }

    MAX-ACCESS read-write
    STATUS current
    DESCRIPTION
      "
      Active radio setting.
      Default value: txRadio1(1)
      "
    ::= { xfRLProtectionEntry 4 }

  xfRLSwitchOverReset OBJECT-TYPE
    SYNTAX INTEGER { reset(1) }
    MAX-ACCESS read-write
    STATUS current
    DESCRIPTION
      "
      Reset of the activated external alarms Tx Switch Over and Remote Tx Switch
      Over by resetting internal alarms.
      "
    ::= { xfRLProtectionEntry 5 }

  xfRLSwitchRevertiveTx OBJECT-TYPE
    SYNTAX INTEGER { txRadio1(1), txRadio2(2), off(3) }
    MAX-ACCESS read-write
    STATUS current
    DESCRIPTION
      "
      Preferred Tx Radio.
      Default value: off(3)
      Near end access: read-write
      Far end access: read-only (Traffic Node only)
      "
    ::= { xfRLProtectionEntry 6 }

  xfRLProtectionCapability OBJECT-TYPE
    SYNTAX BITS
    {
      revertiveSwitching(0),
      txSwitchOverConfiguration(1)
    }
    MAX-ACCESS read-only
    STATUS current
    DESCRIPTION
      "
      This object shows the protection capabilities of the
      traffic node.

      Near end access: read-only
      Far end access: read-only
      "
    ::={ xfRLProtectionEntry 7 }

  xfRLTxSwitchOverConfiguration OBJECT-TYPE
    SYNTAX INTEGER { other(1), disabled(2), enabled(3) }
    MAX-ACCESS read-write
    STATUS current
    DESCRIPTION
      "
      Indicates whether the remote Tx switching function and
      Tx switchover alarm are enabled. When disabled, the
      remote Tx switching function is disabled and Tx switchover
      alarm is never raised and xfRLSwitchOverReset is never
      needed to reset these alarms.
      - Other (1)
      - Disabled (2)  (default)
      - Enabled (3)

      Near end access: read-write
      Far end access: read-write
      "
    ::= { xfRLProtectionEntry 8 }

------------------------------------------------------------------------------
-- xfRLLineProtectionTable
------------------------------------------------------------------------------
  xfRLLineProtectionTable OBJECT-TYPE
    SYNTAX SEQUENCE OF XfRLLineProtectionEntry
    MAX-ACCESS not-accessible
    STATUS current
    DESCRIPTION
      "
      Table for line protection status.
      "
    ::= { xfRadioLinkPtpTerminalObjects  6 }

  xfRLLineProtectionEntry OBJECT-TYPE
    SYNTAX XfRLLineProtectionEntry
    MAX-ACCESS not-accessible
    STATUS current
    DESCRIPTION
      "An entry in the xfRLLineProtectionTable"
    INDEX { ifIndex }
    ::= { xfRLLineProtectionTable 1 }

  XfRLLineProtectionEntry ::=
    SEQUENCE
    {
      xfRLLineProtectionStatus    BITS,
      xfRLLineProtectionMode      INTEGER
    }

--
-- The xfRLLineProtectionTable MOs
--

  xfRLLineProtectionStatus OBJECT-TYPE
    SYNTAX BITS
    {
      hitlessPhase0(0),
      hitlessPhase1(1),
      hitlessPhase2(2),
      txSwitchover0(3),
      txSwitchover1(4),
      txSwitchover2(5),
      remoteTxSwitchOver0(6),
      remoteTxSwitchOver1(7),
      remoteTxSwitchOver2(8),
      rfInputThresholdProtection0(9),
      rfInputThresholdProtection1(10),
      rfInputThresholdProtection2(11)
    }
    MAX-ACCESS read-only
    STATUS current
    DESCRIPTION
      "
      Extension to xfLineProtectionStatus.
      "
    ::= { xfRLLineProtectionEntry 1 }

  xfRLLineProtectionMode OBJECT-TYPE
    SYNTAX INTEGER
    {
      other(1),
      unProtected(2),
      singleInterfaceLowSlot(3),
      singleInterfaceHighSlot(4),
      opticalSplitter(5),
      equipmentAndLineProtection(6)
    }
    MAX-ACCESS read-only
    STATUS current
    DESCRIPTION
      "
      Operational status of the line
      protection for a terminal physical
      line interface, e.g. MMU2 E and
      MMU2 F.
      Administrative status is
      xfTermLineProtection.
      "
    ::= { xfRLLineProtectionEntry 2 }

------------------------------------------------------------------------------
-- xfRADIORSTable
------------------------------------------------------------------------------
  xfRADIORSTable OBJECT-TYPE
    SYNTAX SEQUENCE OF XfRADIORSEntry
    MAX-ACCESS not-accessible
    STATUS current
    DESCRIPTION
      "
      Traffic node extension of ifTable. The tabled is indexed with ifIndex.
      "
    ::= { xfRadioLinkPtpTerminalObjects 7 }

  xfRADIORSEntry OBJECT-TYPE
    SYNTAX XfRADIORSEntry
    MAX-ACCESS not-accessible
    STATUS current
    DESCRIPTION
      "An entry in the xfRADIORSTable"
    INDEX { ifIndex}
    ::= { xfRADIORSTable 1 }

  XfRADIORSEntry ::=
    SEQUENCE
    {
      xfRADIORSAlarms                 BITS
    }

--
-- The xfRADIORSTable MOs
--
  xfRADIORSAlarms OBJECT-TYPE
    SYNTAX BITS
    {
      timRadioSide0(0),
      timRadioSide1(1),
      timRadioSide2(2)
    }
    MAX-ACCESS read-only
    STATUS current
    DESCRIPTION
      "
      This object shows rau rs related alarms.
      "
    ::= { xfRADIORSEntry 1 }

------------------------------------------------------------------------------
-- xfRADIORSPerformanceTable
------------------------------------------------------------------------------

  xfRADIORSPerformanceTable OBJECT-TYPE
    SYNTAX SEQUENCE OF XfRADIORSPerformanceEntry
    MAX-ACCESS not-accessible
    STATUS current
    DESCRIPTION
      "
      Traffic node extension of ifTable. The tabled is indexed with
      ifIndex.
      "
    ::= { xfRadioLinkPtpTerminalObjects 8 }

  xfRADIORSPerformanceEntry OBJECT-TYPE
    SYNTAX XfRADIORSPerformanceEntry
    MAX-ACCESS not-accessible
    STATUS current
    DESCRIPTION
      "An entry in the xfRADIORSPerformanceTable"
    INDEX { ifIndex}
    ::= { xfRADIORSPerformanceTable 1 }

  XfRADIORSPerformanceEntry ::=
    SEQUENCE
    {
      xfRADIORSPerformanceAlarms    BITS
    }

--
-- The xfRADIORSPerformanceTable MOs
--
  xfRADIORSPerformanceAlarms OBJECT-TYPE
    SYNTAX BITS
    {
      b1UnavailablePeriod0(0),
      b1UnavailablePeriod1(1),
      b1UnavailablePeriod2(2),

      b1Es15m0(3),
      b1Es15m1(4),
      b1Es15m2(5),

      b1Ses15m0(6),
      b1Ses15m1(7),
      b1Ses15m2(8),

      b1Bbe15m0(9),
      b1Bbe15m1(10),
      b1Bbe15m2(11),

      b1Es24h0(12),
      b1Es24h1(13),
      b1Es24h2(14),

      b1Ses24h0(15),
      b1Ses24h1(16),
      b1Ses24h2(17),

      b1Bbe24h0(18),
      b1Bbe24h1(19),
      b1Bbe24h2(20)
    }
    MAX-ACCESS read-only
    STATUS current
    DESCRIPTION
      "
      This object shows RAU RS related alarms.
      "
    ::= { xfRADIORSPerformanceEntry 1 }

------------------------------------------------------------------------------
-- xfRLPMConfigTable
------------------------------------------------------------------------------

        xfRLPMConfigTable OBJECT-TYPE
            SYNTAX SEQUENCE OF XfRLPMConfigEntry
            MAX-ACCESS not-accessible
            STATUS current
            DESCRIPTION
                "This table contains the alarm threshold values for RL PM"
            ::= { xfRadioLinkPtpTerminalObjects 9 }

        xfRLPMConfigEntry OBJECT-TYPE
            SYNTAX XfRLPMConfigEntry
            MAX-ACCESS not-accessible
            STATUS current
            DESCRIPTION
                "Entry in the xfRLPMConfigTable."
            INDEX { ifIndex }
            ::= { xfRLPMConfigTable 1 }

        XfRLPMConfigEntry ::=
            SEQUENCE {
                xfPMSetThreshold15mESs
                    Integer32,
                xfPMSetThreshold15mSESs
                    Integer32,
                xfPMSetThreshold15mBBEs
                    Integer32,
                xfPMResetThreshold15mESs
                    Integer32,
                xfPMResetThreshold15mSESs
                    Integer32,
                xfPMResetThreshold15mBBEs
                    Integer32,
                xfPMSetThreshold24hESs
                    Integer32,
                xfPMSetThreshold24hSESs
                    Integer32,
                xfPMSetThreshold24hBBEs
                    Integer32,
                xfPMView
                    INTEGER,
                xfPMStatus
                    BITS,
                xfPMRLTS1Threshold
                    Integer32,
                xfPMSetThreshold15mRLTS1
                   Integer32,
                xfPMResetThreshold15mRLTS1
                   Integer32,
                xfPMRLTS2Threshold
                   Integer32,
                xfPMSetThreshold15mRLTS2
                   Integer32,
                xfPMResetThreshold15mRLTS2
                   Integer32,
                xfPMSetThreshold15mRLTM
                   Integer32,
                xfPMResetThreshold15mRLTM
                   Integer32,
                xfPMTLTS1Threshold
                   Integer32,
                xfPMSetThreshold15mTLTS1
                   Integer32,
                xfPMResetThreshold15mTLTS1
                   Integer32,
                xfPMSetThreshold15mTLTM
                   Integer32,
                xfPMResetThreshold15mTLTM
                   Integer32,
                xfPMSetThreshold24hRLTS1
                   Integer32,
                xfPMSetThreshold24hRLTS2
                   Integer32,
                xfPMSetThreshold24hRLTM
                   Integer32,
                xfPMSetThreshold24hTLTS1
                   Integer32,
                xfPMSetThreshold24hTLTM
                   Integer32
             }

--
-- The xfRLPMConfigTable MOs
--

        xfPMSetThreshold15mESs OBJECT-TYPE
            SYNTAX Integer32
            MAX-ACCESS read-write
            STATUS current
            DESCRIPTION
                "The 15 minute set threshold for ES.
                Default value is 180.
                Near end access: read-write
                Far end access: No access
                "
            ::= { xfRLPMConfigEntry 1 }

        xfPMSetThreshold15mSESs OBJECT-TYPE
            SYNTAX Integer32
            MAX-ACCESS read-write
            STATUS current
            DESCRIPTION
                "The 15 minute set threshold for SES.
                Default value is 15.
                Near end access: read-write
                Far end access: No access
                "
            ::= { xfRLPMConfigEntry 2 }

        xfPMSetThreshold15mBBEs OBJECT-TYPE
            SYNTAX Integer32
            MAX-ACCESS read-write
            STATUS current
            DESCRIPTION
                "The 15 minute set threshold for BBE.
                Default value is 9900.
                Near end access: read-write
                Far end access: No access
                "
            ::= { xfRLPMConfigEntry 3 }

        xfPMResetThreshold15mESs OBJECT-TYPE
            SYNTAX Integer32
            MAX-ACCESS read-write
            STATUS current
            DESCRIPTION
                "The 15 minute reset threshold for ES.
                Default value is 20.
                Near end access: read-write
                Far end access: No access
                "
            ::= { xfRLPMConfigEntry 4 }

        xfPMResetThreshold15mSESs OBJECT-TYPE
            SYNTAX Integer32
            MAX-ACCESS read-write
            STATUS current
            DESCRIPTION
                "The 15 minute reset threshold for SES.
                Default value is 1.
                Near end access: read-write
                Far end access: No access
                "
            ::= { xfRLPMConfigEntry 5 }

        xfPMResetThreshold15mBBEs OBJECT-TYPE
            SYNTAX Integer32
            MAX-ACCESS read-write
            STATUS current
            DESCRIPTION
                "The 15 minute reset threshold for BBE.
                Default value is 200.
                Near end access: read-write
                Far end access: No access
                "
            ::= { xfRLPMConfigEntry 6 }

        xfPMSetThreshold24hESs OBJECT-TYPE
            SYNTAX Integer32
            MAX-ACCESS read-write
            STATUS current
            DESCRIPTION
                "The 24 hours set threshold for ES.
                Default value is 1500.
                Near end access: read-write
                Far end access: No access
                "
            ::= { xfRLPMConfigEntry 7 }

        xfPMSetThreshold24hSESs OBJECT-TYPE
            SYNTAX Integer32
            MAX-ACCESS read-write
            STATUS current
            DESCRIPTION
                "The 24 hours set threshold for SES.
                Default value is 20.
                Near end access: read-write
                Far end access: No access
                "
            ::= { xfRLPMConfigEntry 8 }

        xfPMSetThreshold24hBBEs OBJECT-TYPE
            SYNTAX Integer32
            MAX-ACCESS read-write
            STATUS current
            DESCRIPTION
                "The 24 hours set threshold for BBE.
                Default value is 48000.
                Near end access: read-write
                Far end access: No access
                "
            ::= { xfRLPMConfigEntry 9 }

        xfPMView OBJECT-TYPE
            SYNTAX INTEGER
                {
                pmEnable(1),
                pmDisable(2)
                }
            MAX-ACCESS read-write
            STATUS current
            DESCRIPTION
                "
                Enable/disable visibility of PM tables.
                Default value: pmEnable(1)
                Near end access: read-write
                Far end access: No access
                "
            ::= { xfRLPMConfigEntry 10 }

        xfPMStatus OBJECT-TYPE
            SYNTAX BITS
            {
                unavailablePeriod0(0),
                unavailablePeriod1(1),
                unavailablePeriod2(2),

                es15m0(3),
                es15m1(4),
                es15m2(5),

                ses15m0(6),
                ses15m1(7),
                ses15m2(8),

                bbe15m0(9),
                bbe15m1(10),
                bbe15m2(11),

                es24h0(12),
                es24h1(13),
                es24h2(14),

                ses24h0(15),
                ses24h1(16),
                ses24h2(17),

                bbe24h0(18),
                bbe24h1(19),
                bbe24h2(20),

-- Begin: these alarms are related to obsoleted MOs, they are not meaningful anymore
                rlts1Counter15m0(21),
                rlts1Counter15m1(22),
                rlts1Counter15m2(23),

                rlts2Counter15m0(24),
                rlts2Counter15m1(25),
                rlts2Counter15m2(26),

                rltmCounter15m0(27),
                rltmCounter15m1(28),
                rltmCounter15m2(29),

                tlts1Counter15m0(30),
                tlts1Counter15m1(31),
                tlts1Counter15m2(32),

                tltmCounter15m0(33),
                tltmCounter15m1(34),
                tltmCounter15m2(35),

                rlts1Counter24h0(36),
                rlts1Counter24h1(37),
                rlts1Counter24h2(38),

                rlts2Counter24h0(39),
                rlts2Counter24h1(40),
                rlts2Counter24h2(41),

                rltmCounter24h0(42),
                rltmCounter24h1(43),
                rltmCounter24h2(44),

                tlts1Counter24h0(45),
                tlts1Counter24h1(46),
                tlts1Counter24h2(47),

                tltmCounter24h0(48),
                tltmCounter24h1(49),
                tltmCounter24h2(50)
-- End: these alarms are related to obsoleted MOs
            }
            MAX-ACCESS read-only
            STATUS current
            DESCRIPTION
                "Threshold alarm status.
                 Values from rlts1Counter15m0(21) to tltmCounter24h2(50)
                 are related to obsoleted MOs."
            ::= { xfRLPMConfigEntry 11 }

        xfPMRLTS1Threshold OBJECT-TYPE
            SYNTAX Integer32 (-999..-201)
            MAX-ACCESS read-write
            STATUS current
            DESCRIPTION
                "RLTS1 Alarm Threshold for Minimum RF Input Power.
                RF input level = value/10 dBm.
                Domain: [-99.9 ... -20.1 dBm]
                Valid for both 15 m & 24 h intervals.
                If changed current interval PM data must be reset.
                Always less than RLTS2, xfPMRLTS2Threshold."
            DEFVAL {-999}
            ::= { xfRLPMConfigEntry 12 }

        xfPMSetThreshold15mRLTS1 OBJECT-TYPE
            SYNTAX Integer32 (1..900)
            MAX-ACCESS read-write
            STATUS current
            DESCRIPTION
                "Received Level 1 Threshold Second (RLTS1) 15 minute.
                Alarm Set threshold in number of seconds that
                RF Input Power are allowed below the
                RLTS1 Alarm Threshold for Minimum RF Input Power
                in current 15 minute interval.
                Always greater than alarm Reset, xfPMResetThreshold15mRLTS1."
            DEFVAL {150}
            ::= { xfRLPMConfigEntry 13 }

        xfPMResetThreshold15mRLTS1 OBJECT-TYPE
            SYNTAX Integer32 (1..900)
            MAX-ACCESS read-write
            STATUS current
            DESCRIPTION
                "Received Level 1 Threshold Second (RLTS1) 15 minute.
                Alarm Reset threshold in number of seconds that
                RF Input Power are allowed below the
                RLTS1 Alarm Threshold for Minimum RF Input Power
                for entire current 15 minute interval.
                Always less than alarm Set, xfPMSetThreshold15mRLTS1."
            DEFVAL {1}
            ::= { xfRLPMConfigEntry 14 }

        xfPMRLTS2Threshold OBJECT-TYPE
            SYNTAX Integer32 (-998..-200)
            MAX-ACCESS read-write
            STATUS current
            DESCRIPTION
                "RLTS2 Alarm Threshold for Minimum RF Input Power.
                RF input level = value/10 dBm.
                Domain: [-99.8 ... -20.0 dBm]
                Valid for both 15 m & 24 h intervals.
                If changed current interval PM data must be reset.
                Always greater than RLTS1, xfPMRLTS1Threshold."
            DEFVAL {-998}
            ::= { xfRLPMConfigEntry 15 }

        xfPMSetThreshold15mRLTS2 OBJECT-TYPE
            SYNTAX Integer32 (1..900)
            MAX-ACCESS read-write
            STATUS current
            DESCRIPTION
                "Received Level 2 Threshold Second (RLTS2) 15 minute.
                Alarm Set threshold in number of seconds that
                RF Input Power are allowed below the
                RLTS2 Alarm Threshold for Minimum RF Input Power
                in current 15 minute interval.
                Always greater or equal to alarm Reset, xfPMResetThreshold15mRLTS2."
            DEFVAL {180}
            ::= { xfRLPMConfigEntry 16 }

        xfPMResetThreshold15mRLTS2 OBJECT-TYPE
            SYNTAX Integer32 (1..900)
            MAX-ACCESS read-write
            STATUS current
            DESCRIPTION
                "Received Level 2 Threshold Second (RLTS2) 15 minute.
                Alarm Reset threshold in number of seconds that
                RF Input Power are allowed below the
                RLTS2 Alarm Threshold for Minimum RF Input Power
                for entire current 15 minute interval.
                Always less or equal to alarm Set, xfPMSetThreshold15mRLTS2."
            DEFVAL {20}
            ::= { xfRLPMConfigEntry 17 }

        xfPMSetThreshold15mRLTM OBJECT-TYPE
            SYNTAX Integer32 (10..800)
            MAX-ACCESS read-write
            STATUS current
            DESCRIPTION
                "Receive Level Tide Mark (RLTM) 15 minute.
                Alarm Set threshold for maximum allowed
                max / min difference of RF Input Power
                in current 15 minute interval.
                RF input level = value/10 dB.
                Domain: [1.0 ... 80.0 dB]
                Always greater or equal to alarm Reset, xfPMResetThreshold15mRLTM."
            DEFVAL {800}
            ::= { xfRLPMConfigEntry 18 }

        xfPMResetThreshold15mRLTM OBJECT-TYPE
            SYNTAX Integer32 (10..800)
            MAX-ACCESS read-write
            STATUS current
            DESCRIPTION
                "Receive Level Tide Mark (RLTM) 15 minute.
                Alarm Reset threshold for maximum allowed
                max / min difference of RF Input Power
                for entire current 15 minute interval.
                RF input level = value/10 dB.
                Domain: [1.0 ... 80.0 dB]
                Always less or equal to alarm Set, xfPMSetThreshold15mRLTM."
            DEFVAL {790}
            ::= { xfRLPMConfigEntry 19 }

        xfPMTLTS1Threshold OBJECT-TYPE
            SYNTAX Integer32 (-100..45)
            MAX-ACCESS read-write
            STATUS current
            DESCRIPTION
                "TLTS1 Alarm Threshold for Maximum RF Output Power.
                RF output level = value dBm.
                Domain: [-100 ... 45 dBm]
                Valid for both 15 m & 24 h intervals.
                If changed current interval PM data must be reset."
            DEFVAL {45}
            ::= { xfRLPMConfigEntry 20 }

        xfPMSetThreshold15mTLTS1 OBJECT-TYPE
            SYNTAX Integer32 (1..900)
            MAX-ACCESS read-write
            STATUS current
            DESCRIPTION
                "Transmitted Levels 1 Threshold Second (TLTS1) 15 minute.
                Alarm Set threshold in number of seconds that
                RF Output Power are allowed above the
                TLTS1 Alarm Threshold for Maximum RF Output Power
                in current 15 minute interval.
                Always greater or equal to alarm Reset, xfPMResetThreshold15mTLTS1."
            DEFVAL {180}
            ::= { xfRLPMConfigEntry 21 }

        xfPMResetThreshold15mTLTS1 OBJECT-TYPE
            SYNTAX Integer32 (1..900)
            MAX-ACCESS read-write
            STATUS current
            DESCRIPTION
                "Transmitted Levels 1 Threshold Second (TLTS1) 15 minute.
                Alarm Reset threshold in number of seconds that
                RF Output Power are allowed above the
                TLTS1 Alarm Threshold for Maximum RF Output Power
                for entire current 15 minute interval.
                Always less or equal to alarm Set, xfPMSetThreshold15mTLTS1."
            DEFVAL {20}
            ::= { xfRLPMConfigEntry 22 }

        xfPMSetThreshold15mTLTM OBJECT-TYPE
            SYNTAX Integer32 (1..145)
            MAX-ACCESS read-write
            STATUS current
            DESCRIPTION
                "Transmitted Level Tide Mark (TLTM) 15 minute.
                Alarm Set threshold for maximum allowed
                max / min difference of RF Output Power
                in current 15 minute interval.
                RF output level = value dB.
                Domain: [1 ... 145 dB]
                Always greater or equal to alarm Reset, xfPMResetThreshold15mTLTM."
            DEFVAL {145}
            ::= { xfRLPMConfigEntry 23 }

        xfPMResetThreshold15mTLTM OBJECT-TYPE
            SYNTAX Integer32 (1..145)
            MAX-ACCESS read-write
            STATUS current
            DESCRIPTION
                "Transmitted Level Tide Mark (TLTM) 15 minute.
                Alarm Reset threshold for maximum allowed
                max / min difference of RF Output Power
                for entire current 15 minute interval.
                RF output level = value dB.
                Domain: [1 ... 145 dB]
                Always less or equal to alarm Set, xfPMSetThreshold15mTLTM."
            DEFVAL {144}
            ::= { xfRLPMConfigEntry 24 }

        xfPMSetThreshold24hRLTS1 OBJECT-TYPE
            SYNTAX Integer32 (1..86400)
            MAX-ACCESS read-write
            STATUS current
            DESCRIPTION
                "Received Level 1 Threshold Second (RLTS1) 24 hour.
                Alarm Set / Reset threshold in number of seconds that
                RF Input Power are allowed below the
                RLTS1 Alarm Threshold for Minimum RF Input Power
                in current 24 hour interval."
            DEFVAL {20}
            ::= { xfRLPMConfigEntry 25 }

        xfPMSetThreshold24hRLTS2 OBJECT-TYPE
            SYNTAX Integer32 (1..86400)
            MAX-ACCESS read-write
            STATUS current
            DESCRIPTION
                "Received Level 2 Threshold Second (RLTS2) 24 hour.
                Alarm Set / Reset threshold in number of seconds that
                RF Input Power are allowed below the
                RLTS2 Alarm Threshold for Minimum RF Input Power
                in current 24 hour interval."
            DEFVAL {1500}
            ::= { xfRLPMConfigEntry 26 }

        xfPMSetThreshold24hRLTM OBJECT-TYPE
            SYNTAX Integer32 (10..800)
            MAX-ACCESS read-write
            STATUS current
            DESCRIPTION
                "Receive Level Tide Mark (RLTM) 24 hour.
                Alarm Set / Reset threshold for maximum allowed
                max / min difference of RF Input Power
                in current 24 hour interval.
                RF input level = value/10 dB.
                Domain: [1.0 ... 80.0 dB]"
            DEFVAL {800}
            ::= { xfRLPMConfigEntry 27 }

        xfPMSetThreshold24hTLTS1 OBJECT-TYPE
            SYNTAX Integer32 (1..86400)
            MAX-ACCESS read-write
            STATUS current
            DESCRIPTION
                "Transmitted Levels 1 Threshold Second (TLTS1) 24 hour.
                Alarm Set / Reset threshold in number of seconds that
                RF Output Power are allowed above the
                TLTS1 Alarm Threshold for Maximum RF Output Power
                in current 24 hour interval."
            DEFVAL {1500}
            ::= { xfRLPMConfigEntry 28 }

        xfPMSetThreshold24hTLTM OBJECT-TYPE
            SYNTAX Integer32 (1..145)
            MAX-ACCESS read-write
            STATUS current
            DESCRIPTION
                "Transmitted Level Tide Mark (TLTM) 24 hour.
                Alarm Set / Reset threshold for maximum allowed
                max / min difference of RF Output Power
                in current 24 hour interval.
                RF output level = value dB.
                Domain: [1 ... 145 dB]"
            DEFVAL {145}
            ::= { xfRLPMConfigEntry 29 }

------------------------------------------------------------------------------
-- xfRLPMCurrent24hTable
------------------------------------------------------------------------------

        xfRLPMCurrent24hTable OBJECT-TYPE
            SYNTAX SEQUENCE OF XfRLPMCurrent24hEntry
            MAX-ACCESS not-accessible
            STATUS current
            DESCRIPTION
                "TBD"
            ::= { xfRadioLinkPtpTerminalObjects 10 }

        xfRLPMCurrent24hEntry OBJECT-TYPE
            SYNTAX XfRLPMCurrent24hEntry
            MAX-ACCESS not-accessible
            STATUS current
            DESCRIPTION
                "Entry in the xfRLPMCurrent24hTable."
            INDEX { ifIndex }
            ::= { xfRLPMCurrent24hTable 1 }

        XfRLPMCurrent24hEntry ::=
            SEQUENCE {
                xfPMCurrent24hTimeElapsed
                    Counter32,
                xfPMCurrent24hESs
                    PerfCurrentCount,
                xfPMCurrent24hSESs
                    PerfCurrentCount,
                xfPMCurrent24hBBEs
                    HCPerfCurrentCount,
                xfPMCurrent24hUASs
                    PerfCurrentCount,
                xfPMCurrent24hBBs
                    HCPerfCurrentCount,
                xfPMCurrent24hRLTS1
                    Integer32,
                xfPMCurrent24hRLTS2
                    Integer32,
                xfPMCurrent24hRLMin
                    Integer32,
                xfPMCurrent24hRLMax
                    Integer32,
                xfPMCurrent24hTLTS1
                    Integer32,
                xfPMCurrent24hTLMin
                    Integer32,
                xfPMCurrent24hTLMax
                    Integer32,
                xfPMCurrent24hMSEMin
                    Integer32,
                xfPMCurrent24hMSEMax
                    Integer32,
                xfPMCurrent24hXPIMin
                    Integer32,
                xfPMCurrent24hXPIMax
                    Integer32,
                xfPMCurrent24hESR
                    PerfCurrentCount,
                xfPMCurrent24hSESR
                    PerfCurrentCount,
                xfPMCurrent24hBBER
                    HCPerfCurrentCount
             }
--
-- The xfRLPMCurrent24hTable MOs
--
        xfPMCurrent24hTimeElapsed OBJECT-TYPE
            SYNTAX Counter32
            MAX-ACCESS read-only
            STATUS current
            DESCRIPTION
                "The number of seconds that have elapsed since the
                beginning of the current error-measurement period.

                If the current interval exceeds the maximum value,
                the agent will return the maximum value.
                "
            ::= { xfRLPMCurrent24hEntry 1 }

        xfPMCurrent24hESs OBJECT-TYPE
            SYNTAX PerfCurrentCount
            MAX-ACCESS read-only
            STATUS current
            DESCRIPTION
                "Errored Seconds in the current 24-hour interval."
            ::= { xfRLPMCurrent24hEntry 2 }

        xfPMCurrent24hSESs OBJECT-TYPE
            SYNTAX PerfCurrentCount
            MAX-ACCESS read-only
            STATUS current
            DESCRIPTION
                "Severely Errored Seconds in the current 24-hour
                interval."
            ::= { xfRLPMCurrent24hEntry 3 }

        xfPMCurrent24hBBEs OBJECT-TYPE
            SYNTAX HCPerfCurrentCount
            MAX-ACCESS read-only
            STATUS current
            DESCRIPTION
                "Background Block Errors in the current 24 hour interval"
            ::= { xfRLPMCurrent24hEntry 4 }

        xfPMCurrent24hUASs OBJECT-TYPE
            SYNTAX PerfCurrentCount
            MAX-ACCESS read-only
            STATUS current
            DESCRIPTION
                "Unavailable seconds (or Unavailable Time) in the current
                 24 hour interval."
            ::= { xfRLPMCurrent24hEntry 5 }

        xfPMCurrent24hBBs OBJECT-TYPE
            SYNTAX HCPerfCurrentCount
            MAX-ACCESS read-only
            STATUS current
            DESCRIPTION
                "The number of Background Blocks in the current 24
                hour interval."
            ::= { xfRLPMCurrent24hEntry 6 }

        xfPMCurrent24hRLTS1 OBJECT-TYPE
            SYNTAX Integer32 (0..86400|-1)
            MAX-ACCESS read-only
            STATUS current
            DESCRIPTION
                "Received Level 1 Threshold Second (RLTS1) 24 hour.
                Number of seconds that the RF Input Power was below the RLTS1
                in the current 24 hour interval.
                -1 indicates invalid value.
                Reset by xfTermPerfReset."
            ::= { xfRLPMCurrent24hEntry 7 }

        xfPMCurrent24hRLTS2 OBJECT-TYPE
            SYNTAX Integer32 (0..86400|-1)
            MAX-ACCESS read-only
            STATUS current
            DESCRIPTION
                "Received Level 2 Threshold Second (RLTS2) 24 hour.
                Number of seconds that the RF Input Power was below the RLTS2
                in the current 24 hour interval.
                -1 indicates invalid value.
                Reset by xfTermPerfReset."
            ::= { xfRLPMCurrent24hEntry 8 }

        xfPMCurrent24hRLMin OBJECT-TYPE
            SYNTAX Integer32 (-999..-200|0)
            MAX-ACCESS read-only
            STATUS current
            DESCRIPTION
                "Indicate Min RF Input level in current 24 hour interval.
                RF input level = value/10 dBm.
                Domain: [-99.9 ... -20.0 dBm]
                0 (zero) indicates invalid value.
                Reset by xfTermPerfReset."
            ::= { xfRLPMCurrent24hEntry 9 }

        xfPMCurrent24hRLMax OBJECT-TYPE
            SYNTAX Integer32 (-999..-200|0)
            MAX-ACCESS read-only
            STATUS current
            DESCRIPTION
                "Indicate Max RF Input level in current 24 hour interval.
                RF input level = value/10 dBm.
                Domain: [-99.9 ... -20.0 dBm]
                0 (zero) indicates invalid value.
                Reset by xfTermPerfReset."
            ::= { xfRLPMCurrent24hEntry 10 }

        xfPMCurrent24hTLTS1 OBJECT-TYPE
            SYNTAX Integer32 (0..86400|-1)
            MAX-ACCESS read-only
            STATUS current
            DESCRIPTION
                "Transmitted Level 1 Threshold Second (TLTS1) 24 hour.
                Number of seconds that the RF Output Power was above the TLTS1
                in the current 24 hour interval
                -1 indicates invalid value.
                Reset by xfTermPerfReset."
            ::= { xfRLPMCurrent24hEntry 11 }

        xfPMCurrent24hTLMin OBJECT-TYPE
            SYNTAX Integer32 (-100..45|255)
            MAX-ACCESS read-only
            STATUS current
            DESCRIPTION
                "Indicate Min RF Output level in current 24 hour interval.
                RF output level = value dBm.
                Domain: [-100 ... 45 dBm]
                255 indicates invalid value.
                Reset by xfTermPerfReset."
            ::= { xfRLPMCurrent24hEntry 12 }

        xfPMCurrent24hTLMax OBJECT-TYPE
            SYNTAX Integer32 (-100..45|255)
            MAX-ACCESS read-only
            STATUS current
            DESCRIPTION
                "Indicate Max RF Output level in current 24 hour interval.
                RF output level = value dBm.
                Domain: [-100 ... 45 dBm]
                255 indicates invalid value.
                Reset by xfTermPerfReset."
            ::= { xfRLPMCurrent24hEntry 13 }

        xfPMCurrent24hMSEMin OBJECT-TYPE
            SYNTAX Integer32 (-1000..1000|2000)
            MAX-ACCESS read-only
            STATUS current
            DESCRIPTION
                "Indicate Min MSE level
                in current 24 hour interval.
                Input level = value/10 dB.
                Domain: [-100.0 ... 100.0 dB]
                2000 indicates invalid value.
                Reset by xfTermPerfReset."
            ::= { xfRLPMCurrent24hEntry 14 }

        xfPMCurrent24hMSEMax OBJECT-TYPE
            SYNTAX Integer32 (-1000..1000|2000)
            MAX-ACCESS read-only
            STATUS current
            DESCRIPTION
                "Indicate Max MSE level
                in current 24 hour interval.
                Input level = value/10 dB.
                Domain: [-100.0 ... 100.0 dB]
                2000 indicates invalid value.
                Reset by xfTermPerfReset."
            ::= { xfRLPMCurrent24hEntry 15 }

        xfPMCurrent24hXPIMin OBJECT-TYPE
            SYNTAX Integer32 (-1000..1000|2000)
            MAX-ACCESS read-only
            STATUS current
            DESCRIPTION
                "Indicate Min Cross-Polar Interference (XPI) level
                in current 24 hour interval.
                Input level = value/10 dB.
                Domain: [-100.0 ... 100.0 dB]
                2000 indicates invalid value.
                Reset by xfTermPerfReset."
            ::= { xfRLPMCurrent24hEntry 16 }

        xfPMCurrent24hXPIMax OBJECT-TYPE
            SYNTAX Integer32 (-1000..1000|2000)
            MAX-ACCESS read-only
            STATUS current
            DESCRIPTION
                "Indicate Max Cross-Polar Interference (XPI) level
                in current 24 hour interval.
                Input level = value/10 dB.
                Domain: [-100.0 ... 100.0 dB]
                2000 indicates invalid value.
                Reset by xfTermPerfReset."
            ::= { xfRLPMCurrent24hEntry 17 }

        xfPMCurrent24hESR OBJECT-TYPE
            SYNTAX PerfCurrentCount
            MAX-ACCESS read-only
            STATUS current
            DESCRIPTION
           "Error Seconds Ratio in the current 24-hour interval"
            ::= { xfRLPMCurrent24hEntry 18 }

        xfPMCurrent24hSESR OBJECT-TYPE
            SYNTAX PerfCurrentCount
            MAX-ACCESS read-only
            STATUS current
            DESCRIPTION
           "Severely Error Seconds Ratio in the current 24-hour interval"
            ::= { xfRLPMCurrent24hEntry 19 }

        xfPMCurrent24hBBER OBJECT-TYPE
            SYNTAX HCPerfCurrentCount
            MAX-ACCESS read-only
            STATUS current
            DESCRIPTION
           "Background Block Errors Ratio in the current 24-hour interval"
            ::= { xfRLPMCurrent24hEntry 20 }

------------------------------------------------------------------------------
-- xfRLPMInterval24hTable
------------------------------------------------------------------------------

        xfRLPMInterval24hTable OBJECT-TYPE
            SYNTAX SEQUENCE OF XfRLPMInterval24hEntry
            MAX-ACCESS not-accessible
            STATUS current
            DESCRIPTION
                "TBD"
            ::= { xfRadioLinkPtpTerminalObjects 11 }

        xfRLPMInterval24hEntry OBJECT-TYPE
            SYNTAX XfRLPMInterval24hEntry
            MAX-ACCESS not-accessible
            STATUS current
            DESCRIPTION
                "Entry in the xfRLPMInterval24hTable."
            INDEX { ifIndex }
            ::= { xfRLPMInterval24hTable 1 }

        XfRLPMInterval24hEntry ::=
            SEQUENCE {
                xfPMInterval24hESs
                    PerfIntervalCount,
                xfPMInterval24hSESs
                    PerfIntervalCount,
                xfPMInterval24hBBEs
                    HCPerfCurrentCount,
                xfPMInterval24hUASs
                    PerfIntervalCount,
                xfPMInterval24hBBs
                    HCPerfCurrentCount,
                xfPMInterval24hValidData
                    TruthValue,
                xfPMInterval24hRLTS1
                    Integer32,
                xfPMInterval24hRLTS2
                    Integer32,
                xfPMInterval24hRLMin
                    Integer32,
                xfPMInterval24hRLMax
                    Integer32,
                xfPMInterval24hTLTS1
                    Integer32,
                xfPMInterval24hTLMin
                    Integer32,
                xfPMInterval24hTLMax
                    Integer32,
                xfPMInterval24hMSEMin
                    Integer32,
                xfPMInterval24hMSEMax
                    Integer32,
                xfPMInterval24hXPIMin
                    Integer32,
                xfPMInterval24hXPIMax
                    Integer32
             }

--
-- The xfRLPMInterval24hTable MOs
--
        xfPMInterval24hESs OBJECT-TYPE
            SYNTAX PerfIntervalCount
            MAX-ACCESS read-only
            STATUS current
            DESCRIPTION
                "The counter associated with the number of
                Errored Seconds encountered by a SONET/SDH
                Section in the previous 24-hour interval."
            ::= { xfRLPMInterval24hEntry 1 }

        xfPMInterval24hSESs OBJECT-TYPE
            SYNTAX PerfIntervalCount
            MAX-ACCESS read-only
            STATUS current
            DESCRIPTION
                "The counter associated with the number of Severely
                Errored Seconds encountered by a SONET/SDH
                Section in the previous 24-hour interval."
            ::= { xfRLPMInterval24hEntry 2 }

        xfPMInterval24hBBEs OBJECT-TYPE
            SYNTAX HCPerfCurrentCount
            MAX-ACCESS read-only
            STATUS current
            DESCRIPTION
                "The counter associated with the number of
                Coding Violations (Errored Blocks)
                encountered by a SONET/SDH Section in the
                previous 24-hour interval."
            ::= { xfRLPMInterval24hEntry 3 }

        xfPMInterval24hUASs OBJECT-TYPE
            SYNTAX PerfIntervalCount
            MAX-ACCESS read-only
            STATUS current
            DESCRIPTION
                "The number of UnAvailable Seconds encountered by
                a SONET/SDH Section in the previous 24 hour
                interval."
            ::= { xfRLPMInterval24hEntry 4 }

        xfPMInterval24hBBs OBJECT-TYPE
            SYNTAX HCPerfCurrentCount
            MAX-ACCESS read-only
            STATUS current
            DESCRIPTION
                "The number of Background Blocks in a
                SONET/SDH Section in the previous
                24 hour interval."
            ::= { xfRLPMInterval24hEntry 5 }

        xfPMInterval24hValidData OBJECT-TYPE
            SYNTAX TruthValue
            MAX-ACCESS read-only
            STATUS current
            DESCRIPTION
                "This variable indicates whether the data
                for this interval is valid."
            ::= { xfRLPMInterval24hEntry 6 }

        xfPMInterval24hRLTS1 OBJECT-TYPE
            SYNTAX Integer32 (0..86400|-1)
            MAX-ACCESS read-only
            STATUS current
            DESCRIPTION
                "Received Level 1 Threshold Second (RLTS1) 24 hour.
                Number of seconds that the RF Input Power was below the RLTS1
                in the previous 24 hour interval.
                -1 indicates invalid value.
                Reset by xfTermPerfReset."
            ::= { xfRLPMInterval24hEntry 7 }

        xfPMInterval24hRLTS2 OBJECT-TYPE
            SYNTAX Integer32 (0..86400|-1)
            MAX-ACCESS read-only
            STATUS current
            DESCRIPTION
                "Received Level 2 Threshold Second (RLTS2) 24 hour.
                Number of seconds that the RF Input Power was below the RLTS2
                in the previous 24 hour interval.
                -1 indicates invalid value.
                Reset by xfTermPerfReset."
            ::= { xfRLPMInterval24hEntry 8 }

        xfPMInterval24hRLMin OBJECT-TYPE
            SYNTAX Integer32 (-999..-200|0)
            MAX-ACCESS read-only
            STATUS current
            DESCRIPTION
                "Indicate Min RF Input level in previous 24 hour interval.
                RF input level = value/10 dBm.
                Domain: [-99.9 ... -20.0 dBm]
                0 (zero) indicates invalid value.
                Reset by xfTermPerfReset."
            ::= { xfRLPMInterval24hEntry 9 }

        xfPMInterval24hRLMax OBJECT-TYPE
            SYNTAX Integer32 (-999..-200|0)
            MAX-ACCESS read-only
            STATUS current
            DESCRIPTION
                "Indicate Max RF Input level in previous 24 hour interval.
                RF input level = value/10 dBm.
                Domain: [-99.9 ... -20.0 dBm]
                0 (zero) indicates invalid value.
                Reset by xfTermPerfReset."
            ::= { xfRLPMInterval24hEntry 10 }

        xfPMInterval24hTLTS1 OBJECT-TYPE
            SYNTAX Integer32 (0..86400|-1)
            MAX-ACCESS read-only
            STATUS current
            DESCRIPTION
                "Transmitted Level 1 Threshold Second (TLTS1) 24 hour.
                Number of seconds that the RF Output Power was above the TLTS1
                in the previous 24 hour interval
                -1 indicates invalid value.
                Reset by xfTermPerfReset."
            ::= { xfRLPMInterval24hEntry 11 }

        xfPMInterval24hTLMin OBJECT-TYPE
            SYNTAX Integer32 (-100..45|255)
            MAX-ACCESS read-only
            STATUS current
            DESCRIPTION
                "Indicate Min RF Output level in previous 24 hour interval.
                RF output level = value dBm.
                Domain: [-100 ... 45 dBm]
                255 indicates invalid value.
                Reset by xfTermPerfReset."
            ::= { xfRLPMInterval24hEntry 12 }

        xfPMInterval24hTLMax OBJECT-TYPE
            SYNTAX Integer32 (-100..45|255)
            MAX-ACCESS read-only
            STATUS current
            DESCRIPTION
                "Indicate Max RF Output level in previous 24 hour interval.
                RF output level = value dBm.
                Domain: [-100 ... 45 dBm]
                255 indicates invalid value.
                Reset by xfTermPerfReset."
            ::= { xfRLPMInterval24hEntry 13 }

        xfPMInterval24hMSEMin OBJECT-TYPE
            SYNTAX Integer32 (-1000..1000|2000)
            MAX-ACCESS read-only
            STATUS current
            DESCRIPTION
                "Indicate Min MSE level
                in previous 24 hour interval.
                Input level = value/10 dB.
                Domain: [-100.0 ... 100.0 dB]
                2000 indicates invalid value.
                Reset by xfTermPerfReset."
            ::= { xfRLPMInterval24hEntry 14 }

        xfPMInterval24hMSEMax OBJECT-TYPE
            SYNTAX Integer32 (-1000..1000|2000)
            MAX-ACCESS read-only
            STATUS current
            DESCRIPTION
                "Indicate Max MSE level
                in previous 24 hour interval.
                Input level = value/10 dB.
                Domain: [-100.0 ... 100.0 dB]
                2000 indicates invalid value.
                Reset by xfTermPerfReset."
            ::= { xfRLPMInterval24hEntry 15 }

        xfPMInterval24hXPIMin OBJECT-TYPE
            SYNTAX Integer32 (-1000..1000|2000)
            MAX-ACCESS read-only
            STATUS current
            DESCRIPTION
                "Indicate Min Cross-Polar Interference (XPI) level
                in previous 24 hour interval.
                Input level = value/10 dB.
                Domain: [-100.0 ... 100.0 dB]
                2000 indicates invalid value.
                Reset by xfTermPerfReset."
            ::= { xfRLPMInterval24hEntry 16 }

        xfPMInterval24hXPIMax OBJECT-TYPE
            SYNTAX Integer32 (-1000..1000|2000)
            MAX-ACCESS read-only
            STATUS current
            DESCRIPTION
                "Indicate Max Cross-Polar Interference (XPI) level
                in previous 24 hour interval.
                Input level = value/10 dB.
                Domain: [-100.0 ... 100.0 dB]
                2000 indicates invalid value.
                Reset by xfTermPerfReset."
            ::= { xfRLPMInterval24hEntry 17 }

------------------------------------------------------------------------------
-- xfRLPMCurrent15mTable
------------------------------------------------------------------------------

        xfRLPMCurrent15mTable OBJECT-TYPE
            SYNTAX SEQUENCE OF XfRLPMCurrent15mEntry
            MAX-ACCESS not-accessible
            STATUS current
            DESCRIPTION
                "TBD"
            ::= { xfRadioLinkPtpTerminalObjects 12 }

        xfRLPMCurrent15mEntry OBJECT-TYPE
            SYNTAX XfRLPMCurrent15mEntry
            MAX-ACCESS not-accessible
            STATUS current
            DESCRIPTION
                "Entry in the table."
            INDEX { ifIndex }
            ::= { xfRLPMCurrent15mTable 1 }

        XfRLPMCurrent15mEntry ::=
            SEQUENCE {
                xfPMCurrent15mElapsedTime
                    Counter32,
                xfPMCurrent15mESs
                    PerfCurrentCount,
                xfPMCurrent15mSESs
                    PerfCurrentCount,
                xfPMCurrent15mBBEs
                    PerfCurrentCount,
                xfPMCurrent15mUASs
                    PerfCurrentCount,
                xfPMCurrent15mBBs
                    PerfCurrentCount,
                xfPMCurrent15mRLTS1
                    Integer32,
                xfPMCurrent15mRLTS2
                    Integer32,
                xfPMCurrent15mRLMin
                    Integer32,
                xfPMCurrent15mRLMax
                    Integer32,
                xfPMCurrent15mTLTS1
                    Integer32,
                xfPMCurrent15mTLMin
                    Integer32,
                xfPMCurrent15mTLMax
                    Integer32,
                xfPMCurrent15mMSEMin
                    Integer32,
                xfPMCurrent15mMSEMax
                    Integer32,
                xfPMCurrent15mXPIMin
                    Integer32,
                xfPMCurrent15mXPIMax
                    Integer32,
               xfPMCurrent15mESR
                    PerfCurrentCount,
               xfPMCurrent15mSESR
                    PerfCurrentCount,
                xfPMCurrent15mBBER
                    HCPerfCurrentCount
             }

--
-- The xfRLPMCurrent15mTable MOs
--
        xfPMCurrent15mElapsedTime OBJECT-TYPE
            SYNTAX Counter32
            MAX-ACCESS read-only
            STATUS current
            DESCRIPTION
                "The number of seconds that have elapsed since the beginning of
                the current error-measurement period.
                "
            ::= { xfRLPMCurrent15mEntry 1 }

        xfPMCurrent15mESs OBJECT-TYPE
            SYNTAX PerfCurrentCount
            MAX-ACCESS read-only
            STATUS current
            DESCRIPTION
                "Error seconds in the current 15 minute interval."
            ::= { xfRLPMCurrent15mEntry 2 }

        xfPMCurrent15mSESs OBJECT-TYPE
            SYNTAX PerfCurrentCount
            MAX-ACCESS read-only
            STATUS current
            DESCRIPTION
                "Severely error seconds in the current 15 minute interval."
            ::= { xfRLPMCurrent15mEntry 3 }

        xfPMCurrent15mBBEs OBJECT-TYPE
            SYNTAX PerfCurrentCount
            MAX-ACCESS read-only
            STATUS current
            DESCRIPTION
                "Background Block Errors in the current 15 minute interval."
            ::= { xfRLPMCurrent15mEntry 4 }

        xfPMCurrent15mUASs OBJECT-TYPE
            SYNTAX PerfCurrentCount
            MAX-ACCESS read-only
            STATUS current
            DESCRIPTION
                "Unavailable seconds (or Unavailable Time) in the current
                15 minute interval."
            ::= { xfRLPMCurrent15mEntry 5 }

        xfPMCurrent15mBBs OBJECT-TYPE
            SYNTAX PerfCurrentCount
            MAX-ACCESS read-only
            STATUS current
            DESCRIPTION
                "The number of Background Blocks encountered by a SONET/SDH
                Section in the current 15 minute interval."
            ::= { xfRLPMCurrent15mEntry 6 }

        xfPMCurrent15mRLTS1 OBJECT-TYPE
            SYNTAX Integer32 (0..900|-1)
            MAX-ACCESS read-only
            STATUS current
            DESCRIPTION
                "Received Level 1 Threshold Second (RLTS1) 15 minute
                Number of seconds that the RF Input Power was below the RLTS1
                in the current 15 minute interval.
                -1 indicates invalid value.
                Reset by xfTermPerfReset."
            ::= { xfRLPMCurrent15mEntry 7 }

        xfPMCurrent15mRLTS2 OBJECT-TYPE
            SYNTAX Integer32 (0..900|-1)
            MAX-ACCESS read-only
            STATUS current
            DESCRIPTION
                "Received Level 2 Threshold Second (RLTS2) 15 minute
                Number of seconds that the RF Input Power was below the RLTS2
                in the current 15 minute interval.
                -1 indicates invalid value.
                Reset by xfTermPerfReset."
            ::= { xfRLPMCurrent15mEntry 8 }

        xfPMCurrent15mRLMin OBJECT-TYPE
            SYNTAX Integer32 (-999..-200|0)
            MAX-ACCESS read-only
            STATUS current
            DESCRIPTION
                "Indicate Min RF Input level in current 15 minute interval.
                RF input level = value/10 dBm.
                Domain: [-99.9 ... -20.0 dBm]
                0 (zero) indicates invalid value.
                Reset by xfTermPerfReset."
            ::= { xfRLPMCurrent15mEntry 9 }

         xfPMCurrent15mRLMax OBJECT-TYPE
            SYNTAX Integer32 (-999..-200|0)
            MAX-ACCESS read-only
            STATUS current
            DESCRIPTION
                "Indicate Max RF Input level in current 15 minute interval.
                RF input level = value/10 dBm.
                Domain: [-99.9 ... -20.0 dBm]
                0 (zero) indicates invalid value.
                Reset by xfTermPerfReset."
            ::= { xfRLPMCurrent15mEntry 10 }

        xfPMCurrent15mTLTS1 OBJECT-TYPE
            SYNTAX Integer32 (0..900|-1)
            MAX-ACCESS read-only
            STATUS current
            DESCRIPTION
                "Transmitted Level 1 Threshold Second (TLTS1) 15 minute
                Number of seconds that the RF Output Power was above the TLTS1
                in the current 15 minute interval
                -1 indicates invalid value.
                Reset by xfTermPerfReset."
            ::= { xfRLPMCurrent15mEntry 11 }

        xfPMCurrent15mTLMin OBJECT-TYPE
            SYNTAX Integer32 (-100..45|255)
            MAX-ACCESS read-only
            STATUS current
            DESCRIPTION
                "Indicate Min RF Output level in current 15 minute interval.
                RF output level = value dBm.
                Domain: [-100 ... 45 dBm]
                255 indicates invalid value.
                Reset by xfTermPerfReset."
            ::= { xfRLPMCurrent15mEntry 12 }

        xfPMCurrent15mTLMax OBJECT-TYPE
            SYNTAX Integer32 (-100..45|255)
            MAX-ACCESS read-only
            STATUS current
            DESCRIPTION
                "Indicate Max RF Output level in current 15 minute interval.
                RF output level = value dBm.
                Domain: [-100 ... 45 dBm]
                255 indicates invalid value.
                Reset by xfTermPerfReset."
            ::= { xfRLPMCurrent15mEntry 13 }

        xfPMCurrent15mMSEMin OBJECT-TYPE
            SYNTAX Integer32 (-1000..1000|2000)
            MAX-ACCESS read-only
            STATUS current
            DESCRIPTION
                "Indicate Min MSE level
                in current 15 minute interval.
                Input level = value/10 dB.
                Domain: [-100.0 ... 100.0 dB]
                2000 indicates invalid value.
                Reset by xfTermPerfReset."
            ::= { xfRLPMCurrent15mEntry 14 }

        xfPMCurrent15mMSEMax OBJECT-TYPE
            SYNTAX Integer32 (-1000..1000|2000)
            MAX-ACCESS read-only
            STATUS current
            DESCRIPTION
                "Indicate Max MSE level
                in current 15 minute interval.
                Input level = value/10 dB.
                Domain: [-100.0 ... 100.0 dB]
                2000 indicates invalid value.
                Reset by xfTermPerfReset."
            ::= { xfRLPMCurrent15mEntry 15 }

        xfPMCurrent15mXPIMin OBJECT-TYPE
            SYNTAX Integer32 (-1000..1000|2000)
            MAX-ACCESS read-only
            STATUS current
            DESCRIPTION
                "Indicate Min Cross-Polar Interference (XPI) level
                in current 15 minute interval.
                Input level = value/10 dB.
                Domain: [-100.0 ... 100.0 dB]
                2000 indicates invalid value.
                Reset by xfTermPerfReset."
            ::= { xfRLPMCurrent15mEntry 16 }

        xfPMCurrent15mXPIMax OBJECT-TYPE
            SYNTAX Integer32 (-1000..1000|2000)
            MAX-ACCESS read-only
            STATUS current
            DESCRIPTION
                "Indicate Max Cross-Polar Interference (XPI) level
                in current 15 minute interval.
                Input level = value/10 dB.
                Domain: [-100.0 ... 100.0 dB]
                2000 indicates invalid value.
                Reset by xfTermPerfReset."
            ::= { xfRLPMCurrent15mEntry 17 }

        xfPMCurrent15mESR OBJECT-TYPE
            SYNTAX PerfCurrentCount
            MAX-ACCESS read-only
            STATUS current
            DESCRIPTION
           "Error Seconds Ratio in the current 15 minute interval"
            ::= { xfRLPMCurrent15mEntry 18 }

        xfPMCurrent15mSESR OBJECT-TYPE
            SYNTAX PerfCurrentCount
            MAX-ACCESS read-only
            STATUS current
            DESCRIPTION
           "Severely Error Seconds Ratio in the current 15 minute interval"
            ::= { xfRLPMCurrent15mEntry 19 }

        xfPMCurrent15mBBER OBJECT-TYPE
            SYNTAX HCPerfCurrentCount
            MAX-ACCESS read-only
            STATUS current
            DESCRIPTION
           "Background Block Errors Ratio in the current 15 minute interval"
            ::= { xfRLPMCurrent15mEntry 20 }

------------------------------------------------------------------------------
-- xfRLPMInterval15mTable
------------------------------------------------------------------------------

        xfRLPMInterval15mTable OBJECT-TYPE
            SYNTAX SEQUENCE OF XfRLPMInterval15mEntry
            MAX-ACCESS not-accessible
            STATUS current
            DESCRIPTION
                "TBD"
            ::= { xfRadioLinkPtpTerminalObjects 13 }

        xfRLPMInterval15mEntry OBJECT-TYPE
            SYNTAX XfRLPMInterval15mEntry
            MAX-ACCESS not-accessible
            STATUS current
            DESCRIPTION
                "Entry in the table."
            INDEX { ifIndex, xfPMInterval15mIntervalNumber }
            ::= { xfRLPMInterval15mTable 1 }

        XfRLPMInterval15mEntry ::=
            SEQUENCE {
                xfPMInterval15mIntervalNumber
                    Integer32,
                xfPMInterval15mESs
                    PerfIntervalCount,
                xfPMInterval15mSESs
                    PerfIntervalCount,
                xfPMInterval15mBBEs
                    PerfIntervalCount,
                xfPMInterval15mUASs
                    PerfIntervalCount,
                xfPMInterval15mBBs
                    PerfIntervalCount,
                xfPMInterval15mValidData
                    TruthValue,
                xfPMInterval15mRLTS1
                    Integer32,
                xfPMInterval15mRLTS2
                    Integer32,
                xfPMInterval15mRLMin
                    Integer32,
                xfPMInterval15mRLMax
                    Integer32,
                xfPMInterval15mTLTS1
                    Integer32,
                xfPMInterval15mTLMin
                    Integer32,
                xfPMInterval15mTLMax
                    Integer32,
                xfPMInterval15mMSEMin
                    Integer32,
                xfPMInterval15mMSEMax
                    Integer32,
                xfPMInterval15mXPIMin
                    Integer32,
                xfPMInterval15mXPIMax
                    Integer32
             }

--
-- The xfRLPMInterval15mTable MOs
--
        xfPMInterval15mIntervalNumber OBJECT-TYPE
            SYNTAX Integer32 (1..96)
            MAX-ACCESS read-only
            STATUS current
            DESCRIPTION
                "A number between 1 and 96, which identifies the interval for which
                the set of statistics is available. The interval identified by 1
                is the most recently completed 15 minute interval, and the interval
                identified by N is the interval immediately preceding the one
                identified by N-1."
            ::= { xfRLPMInterval15mEntry 1 }

        xfPMInterval15mESs OBJECT-TYPE
            SYNTAX PerfIntervalCount
            MAX-ACCESS read-only
            STATUS current
            DESCRIPTION
                "Error seconds in the xfPMInterval15mIntervalNumber 15 minute interval"
            ::= { xfRLPMInterval15mEntry 2 }

        xfPMInterval15mSESs OBJECT-TYPE
            SYNTAX PerfIntervalCount
            MAX-ACCESS read-only
            STATUS current
            DESCRIPTION
                "Severely error seconds in the xfPDHCompInterval15mIntervalNumber
                15 minute interval."
            ::= { xfRLPMInterval15mEntry 3 }

        xfPMInterval15mBBEs OBJECT-TYPE
            SYNTAX PerfIntervalCount
            MAX-ACCESS read-only
            STATUS current
            DESCRIPTION
                "Background Block Errors in the xfPDHCompInterval15mIntervalNumber
                15 minute intervall."
            ::= { xfRLPMInterval15mEntry 4 }

        xfPMInterval15mUASs OBJECT-TYPE
            SYNTAX PerfIntervalCount
            MAX-ACCESS read-only
            STATUS current
            DESCRIPTION
                "UnAvailable Seconds in the xfPDHCompInterval15mIntervalNumber
                15 minute interval."
            ::= { xfRLPMInterval15mEntry 5 }

        xfPMInterval15mBBs OBJECT-TYPE
            SYNTAX PerfIntervalCount
            MAX-ACCESS read-only
            STATUS current
            DESCRIPTION
                "Background blocks in the xfPDHCompInterval15mIntervalNumber 15 minute interval."
            ::= { xfRLPMInterval15mEntry 6 }

        xfPMInterval15mValidData OBJECT-TYPE
            SYNTAX TruthValue
            MAX-ACCESS read-only
            STATUS current
            DESCRIPTION
                "This variable indicates if the data for this interval is valid."
            ::= { xfRLPMInterval15mEntry 7 }

        xfPMInterval15mRLTS1 OBJECT-TYPE
            SYNTAX Integer32 (0..900|-1)
            MAX-ACCESS read-only
            STATUS current
            DESCRIPTION
                "Received Level 1 Threshold Second (RLTS1) 15 minute
                Number of seconds that the RF Input Power was below the RLTS1
                in the previous 15 minute interval.
                -1 indicates invalid value.
                Reset by xfTermPerfReset."
            ::= { xfRLPMInterval15mEntry 8 }

        xfPMInterval15mRLTS2 OBJECT-TYPE
            SYNTAX Integer32 (0..900|-1)
            MAX-ACCESS read-only
            STATUS current
            DESCRIPTION
                "Received Level 2 Threshold Second (RLTS2) 15 minute
                Number of seconds that the RF Input Power was below the RLTS2
                in the previous 15 minute interval.
                -1 indicates invalid value.
                Reset by xfTermPerfReset."
            ::= { xfRLPMInterval15mEntry 9 }

        xfPMInterval15mRLMin OBJECT-TYPE
            SYNTAX Integer32 (-999..-200|0)
            MAX-ACCESS read-only
            STATUS current
            DESCRIPTION
                "Indicate Min RF Input level in previous 15 minute interval.
                RF input level = value/10 dBm.
                Domain: [-99.9 ... -20.0 dBm]
                0 (zero) indicates invalid value.
                Reset by xfTermPerfReset."
            ::= { xfRLPMInterval15mEntry 10 }

         xfPMInterval15mRLMax OBJECT-TYPE
            SYNTAX Integer32 (-999..-200|0)
            MAX-ACCESS read-only
            STATUS current
            DESCRIPTION
                "Indicate Max RF Input level in previous 15 minute interval.
                RF input level = value/10 dBm.
                Domain: [-99.9 ... -20.0 dBm]
                0 (zero) indicates invalid value.
                Reset by xfTermPerfReset."
            ::= { xfRLPMInterval15mEntry 11 }

        xfPMInterval15mTLTS1 OBJECT-TYPE
            SYNTAX Integer32 (0..900|-1)
            MAX-ACCESS read-only
            STATUS current
            DESCRIPTION
                "Transmitted Level 1 Threshold Second (TLTS1) 15 minute
                Number of seconds that the RF Output Power was above the TLTS1
                in the previous 15 minute interval
                -1 indicates invalid value.
                Reset by xfTermPerfReset."
            ::= { xfRLPMInterval15mEntry 12 }

        xfPMInterval15mTLMin OBJECT-TYPE
            SYNTAX Integer32 (-100..45|255)
            MAX-ACCESS read-only
            STATUS current
            DESCRIPTION
                "Indicate Min RF Output level in previous 15 minute interval.
                RF output level = value dBm.
                Domain: [-100 ... 45 dBm]
                255 indicates invalid value.
                Reset by xfTermPerfReset."
            ::= { xfRLPMInterval15mEntry 13 }

        xfPMInterval15mTLMax OBJECT-TYPE
            SYNTAX Integer32 (-100..45|255)
            MAX-ACCESS read-only
            STATUS current
            DESCRIPTION
                "Indicate Max RF Output level in previous 15 minute interval.
                RF output level = value dBm.
                Domain: [-100 ... 45 dBm]
                255 indicates invalid value.
                Reset by xfTermPerfReset."
            ::= { xfRLPMInterval15mEntry 14 }

        xfPMInterval15mMSEMin OBJECT-TYPE
            SYNTAX Integer32 (-1000..1000|2000)
            MAX-ACCESS read-only
            STATUS current
            DESCRIPTION
                "Indicate Min MSE level
                in previous 15 minute interval.
                Input level = value/10 dB.
                Domain: [-100.0 ... 100.0 dB]
                2000 indicates invalid value.
                Reset by xfTermPerfReset."
            ::= { xfRLPMInterval15mEntry 15 }

        xfPMInterval15mMSEMax OBJECT-TYPE
            SYNTAX Integer32 (-1000..1000|2000)
            MAX-ACCESS read-only
            STATUS current
            DESCRIPTION
                "Indicate Max MSE level
                in previous 15 minute interval.
                Input level = value/10 dB.
                Domain: [-100.0 ... 100.0 dB]
                2000 indicates invalid value.
                Reset by xfTermPerfReset."
            ::= { xfRLPMInterval15mEntry 16 }

        xfPMInterval15mXPIMin OBJECT-TYPE
            SYNTAX Integer32 (-1000..1000|2000)
            MAX-ACCESS read-only
            STATUS current
            DESCRIPTION
                "Indicate Min Cross-Polar Interference (XPI) level
                in previous 15 minute interval.
                Input level = value/10 dB.
                Domain: [-100.0 ... 100.0 dB]
                2000 indicates invalid value.
                Reset by xfTermPerfReset."
            ::= { xfRLPMInterval15mEntry 17 }

        xfPMInterval15mXPIMax OBJECT-TYPE
            SYNTAX Integer32 (-1000..1000|2000)
            MAX-ACCESS read-only
            STATUS current
            DESCRIPTION
                "Indicate Max Cross-Polar Interference (XPI) level
                in previous 15 minute interval.
                Input level = value/10 dB.
                Domain: [-100.0 ... 100.0 dB]
                2000 indicates invalid value.
                Reset by xfTermPerfReset."
            ::= { xfRLPMInterval15mEntry 18 }

------------------------------------------------------------------------------
-- xfRLPtpTerminalXTable
------------------------------------------------------------------------------

        xfRLPtpTerminalXTable OBJECT-TYPE
            SYNTAX SEQUENCE OF XfRLPtpTerminalXEntry
            MAX-ACCESS not-accessible
            STATUS current
            DESCRIPTION
            "Extension table to xfRLPtpTerminalTable.
             The table is indexed with entLogicalIndex."
            ::= { xfRadioLinkPtpTerminalObjects 14 }

        xfRLPtpTerminalXEntry OBJECT-TYPE
            SYNTAX XfRLPtpTerminalXEntry
            MAX-ACCESS not-accessible
            STATUS current
            DESCRIPTION
            "Entry in the table"
            INDEX { entLogicalIndex }
            ::= { xfRLPtpTerminalXTable 1 }

        XfRLPtpTerminalXEntry ::=
            SEQUENCE {
                xfTermInterfaces                     INTEGER,
                xfTermInterfacesCapability         BITS,
                xfTermChannelModeOperStatus        ChannelMode,
                xfTermXPICRestore                  INTEGER,
                xfTermTribCapacityActual           Integer32,
                xfTermTribCapacityDesired          Integer32,
                xfTermBitPipeCapacity              Integer32,
                xfTermRowIndex                     Integer32,
                xfTermCapabilitiesLastChange       TimeTicks,
                xfTermActualRowIndex               Integer32,
                xfTermMaxRowIndex                  Integer32,
                xfTermAdaptiveManualRowIndex       Integer32,
                xfTermAdaptiveManualMode           TermAdaptiveManualMode,
                xfTermSpectrumEfficiencyClass      INTEGER,
                xfTermSpectrumEfficiencyClassCapability  BITS,
                xfTermIpAddress                    IpAddress,
                xfTermProtectionCapability         BITS,
                xfTermLineProtectionCapability       BITS,
                xfTermTribAllocationActual         BITS,
                xfTermTribAllocationDesired        BITS,
                xfTermAutoRemoveLoopEnable         TermAutoRemoveLoopEnable,
                xfTermCapability                   BITS,
                xfTermCapacityLicense              INTEGER,
                xfTermFadingRates                  INTEGER,
                xfTermFadingRatesCapability        BITS,
                xfTermConfiguredBitPipeCapacity          Integer32,
                xfTermTribCapacityConfigured             Integer32,
                xfTermPacketMaxCapacity            Integer32,
                xfTermPacketMinCapacity            Integer32
             }

--
-- The xfRLPtpTerminalXTable MOs
--
        xfTermInterfaces OBJECT-TYPE
            SYNTAX INTEGER
            {
              other(1),
              pdhToTdmHier(2),
              pdhToTdmFlat(3),
              pdhToTdmFlatAndBitpipeToPtp(4),
              pdhToTdmAndSDHToSFP(5),
              pdhToTdmAndSDHToPtp(6),
              pdhToTdmAndSDHToSFPHAndSDHToPtP(7)
            }
            MAX-ACCESS read-write
            STATUS current
            DESCRIPTION
            "Interface constellation for the terminal"
            ::= { xfRLPtpTerminalXEntry 1 }

        xfTermInterfacesCapability OBJECT-TYPE
            SYNTAX BITS
            {
              pdhToTdmHier(0),
              pdhToTdmFlat(1),
              pdhToTdmFlatAndBitpipeToPtp(2),
              pdhToTdmAndSDHToSFP(3),
              pdhToTdmAndSDHToPtp(4)
            }
            MAX-ACCESS read-only
            STATUS current
            DESCRIPTION
            "Interface constellation capability for the terminal"
            ::= { xfRLPtpTerminalXEntry 2 }

        xfTermChannelModeOperStatus OBJECT-TYPE
            SYNTAX ChannelMode
            MAX-ACCESS read-only
            STATUS current
            DESCRIPTION
            "
            Channel mode for the terminal (operational status).
            - ccdp(2): Co-Channel Dual Polarization (XPIC)
            - accp(3): Adjacent Channels Co-Polarization (non-XPIC)
            - acap(4): Adjacent Channels Alternate Polarization (non-XPIC)
            "
            ::= { xfRLPtpTerminalXEntry 3 }

        xfTermXPICRestore OBJECT-TYPE
            SYNTAX INTEGER
            {
              xPicRestore(1)
            }
            MAX-ACCESS read-write
            STATUS current
            DESCRIPTION
            "Restore XPIC"
            ::= { xfRLPtpTerminalXEntry 4 }

        xfTermTribCapacityActual OBJECT-TYPE
            SYNTAX Integer32
            MAX-ACCESS read-only
            STATUS current
            DESCRIPTION
            "Actual tributary capacity"
            ::= { xfRLPtpTerminalXEntry 5 }

        xfTermTribCapacityDesired OBJECT-TYPE
            SYNTAX Integer32
            MAX-ACCESS read-write
            STATUS current
            DESCRIPTION
            "Desired tributary capacity"
            ::= { xfRLPtpTerminalXEntry 6 }

        xfTermBitPipeCapacity OBJECT-TYPE
            SYNTAX Integer32
            MAX-ACCESS read-only
            STATUS current
            DESCRIPTION
            "Bit pipe capacity, Kbps"
            ::= { xfRLPtpTerminalXEntry 7 }

        xfTermRowIndex OBJECT-TYPE
            SYNTAX Integer32 (1..100000)
            MAX-ACCESS read-write
            STATUS current
            DESCRIPTION
            "Points to a row in xfRlPtpTerminalCapabilityTable"
            ::= { xfRLPtpTerminalXEntry 8 }

        xfTermCapabilitiesLastChange OBJECT-TYPE
            SYNTAX TimeTicks
            MAX-ACCESS read-only
            STATUS current
            DESCRIPTION
            "The value of sysUpTime at the time of the last creation or
             deletion of an entry in the xfRLPtpTerminalCapabilityTable.
             If the number of entries has been unchanged since the last
             re-initialization of the local network management subsystem,
             then this object contains a zero value."
            ::= { xfRLPtpTerminalXEntry 9 }

        xfTermActualRowIndex OBJECT-TYPE
            SYNTAX Integer32
            MAX-ACCESS read-only
            STATUS current
            DESCRIPTION
            "The actual row that is pointed out in xfRlPtpTerminalCapabilityTable"
            ::= { xfRLPtpTerminalXEntry  10 }

        xfTermMaxRowIndex OBJECT-TYPE
            SYNTAX Integer32
            MAX-ACCESS read-write
            STATUS current
            DESCRIPTION
            "Points to a row in xfRlPtpTerminalCapabilityTable where the maximum capacity is, including license"
            ::= { xfRLPtpTerminalXEntry  11 }

        xfTermAdaptiveManualRowIndex OBJECT-TYPE
            SYNTAX Integer32
            MAX-ACCESS read-write
            STATUS current
            DESCRIPTION
            "Manual row index"
            ::= { xfRLPtpTerminalXEntry  12 }

        xfTermAdaptiveManualMode OBJECT-TYPE
            SYNTAX TermAdaptiveManualMode
            MAX-ACCESS read-write
            STATUS current
            DESCRIPTION
            "Adaptive manual mode
            - other(1)
            - disable(2)(default)
            - enable(3)
            - enabledAsRequest(4)
            "
            ::= { xfRLPtpTerminalXEntry  13 }

        xfTermSpectrumEfficiencyClass OBJECT-TYPE
          SYNTAX INTEGER
            {
              other(1),
              sec2(2),
              sec3(3),
              sec4L(4),
              sec4H(5),
              sec5A(6),
              sec5B(7),
              sec6A(8),
              sec6B(9)
            }
          MAX-ACCESS read-write
          STATUS current
          DESCRIPTION
          "Spectrum Efficiency Class:
          - other(1): unknown
          - sec2(2): spectrum eff. Class 2
          - sec3(3): spectrum eff. Class 3
          - sec4L(4): spectrum eff. Class 4L
          - sec4H(5): specturm eff. Class 4H
          - sec5A(6): spectrum eff. Class 5A
          - sec5B(7): spectrum eff. Class 5B
          - sec6A(8): spectrum eff. Class 6A
          - sec6B(9): spectrum eff. Class 6B
          Near end access: read-write
          Far end access: read-write (Traffic Node), read-only (other)"
          ::= { xfRLPtpTerminalXEntry  14 }

        xfTermSpectrumEfficiencyClassCapability OBJECT-TYPE
          SYNTAX BITS
            {
              sec2(0),
              sec3(1),
              sec4L(2),
              sec4H(3),
              sec5A(4),
              sec5B(5),
              sec6A(6),
              sec6B(7)
            }
            MAX-ACCESS read-only
            STATUS current
            DESCRIPTION
            "
            Spectrum Efficiency Class Capability
            - 0 Sec2  Spectrum eff. Class 2
            - 1 Sec3  Specturm eff. Class 3
            - 2 Sec4L Specturm eff. Class 4L
            - 3 Sec4H Spectrum eff. Class 4H
            - 4 Sec5A Spectrum eff. Class 5A
            - 5 Sec5B Spectrum eff. Class 5B
            - 6 Sec6A Spectrum eff. Class 6A
            - 7 Sec6B Spectrum eff. Class 6B
            "
            ::= { xfRLPtpTerminalXEntry  15 }

            xfTermIpAddress OBJECT-TYPE
            SYNTAX IpAddress
            MAX-ACCESS read-only
            STATUS current
            DESCRIPTION
            "LAN ip address"
            ::= { xfRLPtpTerminalXEntry 16 }

       xfTermProtectionCapability OBJECT-TYPE
          SYNTAX BITS
            {
              unprotected(0),
              protectedHotStandby(1),
              protectedWorkingStandby(2),
              unprotectedSD(3),
              nplus1(4),
              enhancedRLB(5)
            }
            MAX-ACCESS read-only
            STATUS current
            DESCRIPTION
            "Terminal protection capability
            - 0 Unprotected ............... The terminal supports 1+0
            - 1 protectedHotStandby ....... The terminal supports 1+1 Hot Standby
            - 2 protectedWorkingStandby ... The terminal supports 1+1 Working Standby
            - 3 unprotectedSD ............. The terminal supports 1+0 with Space diversity
            - 4 nplus1 .................... The terminal supports N+1 protection (through RPS board)
            - 5 enhancedRLB ............... The terminal supports Enhanced Radio Link Bonding
            "
            ::= { xfRLPtpTerminalXEntry  17 }

         xfTermLineProtectionCapability OBJECT-TYPE
          SYNTAX BITS
            {
                unprotected(0),
                singleInterfaceLowSlot(1),
                singleInterfaceHighSlot(2),
                opticalSplitter(3),
                equipmentAndLineProtection(4)
            }
            MAX-ACCESS read-only
            STATUS current
            DESCRIPTION
            "Terminal Line protection capability
            - 0 unprotected .................
            - 1 singleInterfaceLowSlot ......
            - 2 singleInterfaceHighSlot .....
            - 3 opticalSplitter .............
            - 4 equipmentAndLineProtection ..
            "
            ::= { xfRLPtpTerminalXEntry  18 }

        xfTermTribAllocationActual OBJECT-TYPE
            SYNTAX BITS { firstE1(0) }
            MAX-ACCESS read-only
            STATUS current
            DESCRIPTION
            "Actual tributary allocation in a MMU2 D or MMU2 H, the rest is packet link"
            ::= { xfRLPtpTerminalXEntry  19 }

        xfTermTribAllocationDesired OBJECT-TYPE
            SYNTAX BITS { firstE1(0) }
            MAX-ACCESS read-write
            STATUS current
            DESCRIPTION
            "Desired tibutary allocation in a MMU2 D or MMU2 H, the rest is packet link"
            ::= { xfRLPtpTerminalXEntry  20 }

        xfTermAutoRemoveLoopEnable OBJECT-TYPE
            SYNTAX TermAutoRemoveLoopEnable
            MAX-ACCESS read-write
            STATUS current
            DESCRIPTION
            "Auto Remove Loops
            - other(1)
            - enable(2) (default)
            - disable(3)
            "
            ::= { xfRLPtpTerminalXEntry  21 }

        xfTermCapability OBJECT-TYPE
            SYNTAX BITS
              {
                adaptiveManualTx(0),
                adaptiveManualRx(1),
                fragmentedTributaries(2),
                terminalCapacityLicense(3)
              }
            MAX-ACCESS read-only
            STATUS current
            DESCRIPTION
            "Terminal capability"
            ::= { xfRLPtpTerminalXEntry 22 }

        xfTermCapacityLicense OBJECT-TYPE
            SYNTAX INTEGER
            {
              vr0(0),
              vr10(1),
              vr25(2),
              vr50(3),
              vr100(4),
              vr15(5),
              vr30(6),
              vr60(7),
              vr125(8),
              vr200(9),
              vr350(10),
              vr4(11),
              vr500(12),
              vr150(13),
              vr250(14),
              vr300(15),
              vr400(16),
              vr450(17)
            }
            MAX-ACCESS read-write
            STATUS current
            DESCRIPTION
            "Licensetable"
            ::= { xfRLPtpTerminalXEntry 23 }

        xfTermFadingRates OBJECT-TYPE
            SYNTAX INTEGER
            {
              other(1),
              fr50(2),
              fr100(3)
            }
            MAX-ACCESS read-write
            STATUS current
            DESCRIPTION
            "Fading rates
            - other(1): unknown
            - fr50(2): 50dB/s HighTroughputMode (default)
            - fr150(3): 100dB/s HighFadingResistanceMode
            "
            ::= { xfRLPtpTerminalXEntry 24 }

        xfTermFadingRatesCapability OBJECT-TYPE
            SYNTAX BITS
            {
              fr50(0),
              fr100(1)
            }
            MAX-ACCESS read-only
            STATUS current
            DESCRIPTION
            "Fading rate capability
            - fr50(0): HighTroughputMode
            - fr100(1): HighFadingResistanceMode"
            ::= { xfRLPtpTerminalXEntry 25 }

        xfTermConfiguredBitPipeCapacity OBJECT-TYPE
            SYNTAX Integer32
            MAX-ACCESS read-only
            STATUS current
            DESCRIPTION
            "Configured bit pipe capacity, Kbps"
            ::= { xfRLPtpTerminalXEntry 26 }

        xfTermTribCapacityConfigured OBJECT-TYPE
            SYNTAX Integer32
            MAX-ACCESS read-only
            STATUS current
            DESCRIPTION
            "Configured tributary capacity"
            ::= { xfRLPtpTerminalXEntry 27 }

        xfTermPacketMaxCapacity OBJECT-TYPE
            SYNTAX Integer32
            MAX-ACCESS read-only
            STATUS current
            DESCRIPTION
                "Packet Max Capacity"
            ::= { xfRLPtpTerminalXEntry 28 }

        xfTermPacketMinCapacity OBJECT-TYPE
            SYNTAX Integer32
            MAX-ACCESS read-only
            STATUS current
            DESCRIPTION
                "Packet Min Capacity"
            ::= { xfRLPtpTerminalXEntry 29 }
------------------------------------------------------------------------------
-- xfRlPtpTerminalCapabilityTable
------------------------------------------------------------------------------

        xfRlPtpTerminalCapabilityTable OBJECT-TYPE
            SYNTAX SEQUENCE OF XfRlPtpTerminalCapabilityEntry
            MAX-ACCESS not-accessible
            STATUS current
            DESCRIPTION
            "Table for misc. capability informatio."
            ::= { xfRadioLinkPtpTerminalObjects 15 }

        xfRlPtpTerminalCapabilityEntry OBJECT-TYPE
            SYNTAX XfRlPtpTerminalCapabilityEntry
            MAX-ACCESS not-accessible
            STATUS current
            DESCRIPTION
            "Entry in the table"
            INDEX { entLogicalIndex, xfTermRowIndex }
            ::= { xfRlPtpTerminalCapabilityTable 1 }

        XfRlPtpTerminalCapabilityEntry ::=
            SEQUENCE
            {
                xfTermChannelSpacing                  INTEGER,
                xfTermChannelModulation               TermModulation,
                xfTermMaxTribCapacity                 Integer32,
                xfTermDCNCapacity                     Integer32,
                xfTermValidRow                        INTEGER,
                xfTermMaxCapacity                     Integer32,
                xfTermSpectrumEfficiencyClassObsolete TermRauSec,
                xfTermFrameFormatType                 INTEGER,
                xfTermFrameFormatRev                  INTEGER,
                xfTermBerAlarmThresholdCapability      BITS
             }

--
-- The XfRlPtpTerminalCapabilityTable MOs
--
        xfTermChannelSpacing OBJECT-TYPE
            SYNTAX INTEGER
            {
              chspUnknown(0),
              chsp7MHz(1),
              chsp14MHz(2),
              chsp20MHz(3),
              chsp28MHz(4),
              chsp30MHz(5),
              chsp40MHz(6),
              chsp50MHz(7),
              chsp56MHz(8),
              chsp10MHz(9),
              chsp3500kHz(10),
              chsp60MHz(11)
            }
            MAX-ACCESS read-only
            STATUS current
            DESCRIPTION
            "Channel spacing
            - ETSI: 3.5, 7, 14, 28, 40, 56 MHz
            - ANSI: 10, 20, 30, 40, 50, 60 MHz
            "
            ::= { xfRlPtpTerminalCapabilityEntry 1 }

        xfTermChannelModulation OBJECT-TYPE
            SYNTAX TermModulation
            MAX-ACCESS read-only
            STATUS current
            DESCRIPTION
            "Channel modulation
            - cqpsk(2)    CQPSK
            - qam16(3)    16-QAM
            - qam128(4)   128-QAM
            - qam32(5)    32-QAM
            - qam64(6)    64-QAM
            - qam4(7)     4-QAM
            - qam8(8)     8-QAM
            - qam256(9)   256-QAM
            - qam512(10)  512-QAM
            - qam1024(11) 1024-QAM
            "
            ::= { xfRlPtpTerminalCapabilityEntry 2 }

        xfTermMaxTribCapacity OBJECT-TYPE
          SYNTAX Integer32
          MAX-ACCESS read-only
          STATUS current
          DESCRIPTION
          "Max number of tributaries"
          ::= { xfRlPtpTerminalCapabilityEntry 3 }

        xfTermDCNCapacity OBJECT-TYPE
            SYNTAX Integer32
            MAX-ACCESS read-only
            STATUS current
            DESCRIPTION
            "DCN hop capacity"
            ::= { xfRlPtpTerminalCapabilityEntry 4 }

        xfTermValidRow OBJECT-TYPE
            SYNTAX INTEGER
            {
              vr0(0),
              vr10(1),
              vr25(2),
              vr50(3),
              vr100(4),
              vr15(5),
              vr30(6),
              vr60(7),
              vr125(8),
              vr200(9),
              vr350(10),
              vr4(11),
              vr500(12),
              vr150(13),
              vr250(14),
              vr300(15),
              vr400(16),
              vr450(17)
            }
            MAX-ACCESS read-only
            STATUS current
            DESCRIPTION
            "Max capacity license
            - vr0(0)    = invalid row
            - vr10(1)   = 10 Mbps, no license
            - vr25(2)   = 25 Mbps
            - vr50(3)   = 50 Mbps
            - vr100(4)  = 100 Mbps
            - vr15(5)   = 15 Mbps
            - vr30(6)   = 30 Mbps
            - vr60(7)   = 60 Mbps
            - vr125(8)  = 125 Mbps
            - vr200(9)  = 200 Mbps
            - vr350(10) = 350 Mbps
            - vr4(11)   = 4 Mbps, no license
            - vr500(12) = 500 Mbps
            - vr150(13) = 150 Mbps
            - vr250(14) = 250 Mbps
            - vr300(15) = 300 Mbps
            - vr400(16) = 400 Mbps
            - vr450(17) = 450 Mbps
            "
            ::= { xfRlPtpTerminalCapabilityEntry 5 }

        xfTermMaxCapacity OBJECT-TYPE
          SYNTAX Integer32
          MAX-ACCESS read-only
          STATUS current
          DESCRIPTION
          "Max capacity"
          ::= { xfRlPtpTerminalCapabilityEntry 6 }

        xfTermSpectrumEfficiencyClassObsolete OBJECT-TYPE
          SYNTAX TermRauSec
          MAX-ACCESS read-only
          STATUS obsolete
          DESCRIPTION
          "xfTermSpectrumEfficiencyClassObsolete"
          ::= { xfRlPtpTerminalCapabilityEntry 7 }

        xfTermFrameFormatType OBJECT-TYPE
            SYNTAX INTEGER
            {
              fftOther(0),
              fftStatic(1),
              fftAdmod(2),
              fftXpic(3),
              fftXpicAdmod(4),
              fftLegacy(5),
              fftStaticLH(6),
              fftAdmodLH(7),
              fftXpicLH(8),
              fftXpicAdmodLH(9),
              fftAdmodStatic(10),
              fftXpicAdmodStatic(11),
              fftAdmodStaticLH(12),
              fftXpicAdmodStaticLH(13)
            }
            MAX-ACCESS read-only
            STATUS current
            DESCRIPTION
            "Frame format type
            - fftOther(0)
            - fftStatic(1)
            - fftAdmod(2)
            - fftXpic(3)
            - fftXpicAdmod(4)
            - fftLegacy(5)
            - fftStaticLH(6)
            - fftAdmodLH(7)
            - fftXpicLH(8)
            - fftXpicAdmodLH(9)
            - fftAdmodStatic(10)
            - fftXpicAdmodStatic(11)
            - fftAdmodStaticLH(12)
            - fftXpicAdmodStaticLH(13)
            "
            ::= { xfRlPtpTerminalCapabilityEntry 8 }

        xfTermFrameFormatRev OBJECT-TYPE
            SYNTAX INTEGER
            {
              ffOther(1),
              ffVersion0(2),
              ffVersion1(3),
              ffVersion2(4),
              ffVersion3(5),
              ffVersion4(6),
              ffVersion5(7),
              ffVersion6(8),
              ffVersion7(9),
              ffVersion8(10),
              ffVersion9(11),
              ffVersion10(12),
              ffVersion11(13),
              ffVersion12(14),
              ffVersion13(15),
              ffVersion14(16),
              ffVersion15(17)
            }
            MAX-ACCESS read-only
            STATUS current
            DESCRIPTION
            "Frame format revision"
            ::= { xfRlPtpTerminalCapabilityEntry 9 }

        xfTermBerAlarmThresholdCapability OBJECT-TYPE
            SYNTAX BITS
            {
              berThrCap1e3(0),
              berThrCap1e4(1),
              berThrCap1e5(2),
              berThrCap1e6(3)
            }
            MAX-ACCESS read-only
            STATUS current
            DESCRIPTION
            "List of the allowed BER thresholds"
            ::= { xfRlPtpTerminalCapabilityEntry 10 }

------------------------------------------------------------------------------
-- xfRLPMAMConfigTable
------------------------------------------------------------------------------

        xfRLPMAMConfigTable OBJECT-TYPE
            SYNTAX SEQUENCE OF XfRLPMAMConfigEntry
            MAX-ACCESS not-accessible
            STATUS current
            DESCRIPTION
            "Alarm threshold values for RL PM"
            ::= { xfRadioLinkPtpTerminalObjects 16 }

        xfRLPMAMConfigEntry OBJECT-TYPE
            SYNTAX XfRLPMAMConfigEntry
            MAX-ACCESS not-accessible
            STATUS current
            DESCRIPTION
                "Entry in the xfRLPMAMConfigTable"
            INDEX { ifIndex }
            ::= { xfRLPMAMConfigTable 1 }

        XfRLPMAMConfigEntry ::=
            SEQUENCE {
                xfPMAMSetThreshold15m
                    Integer32,
                xfPMAMSetThreshold24h
                    Integer32,
                xfPMAMResetThreshold15m
                    Integer32,
                xfPMAMStatus
                    BITS,
                xfPMAMValidData
                    BITS
             }

--
-- The xfRLPMAMConfigTable MOs
--

        xfPMAMSetThreshold15m OBJECT-TYPE
            SYNTAX Integer32
            MAX-ACCESS read-write
            STATUS current
            DESCRIPTION
                "The 15 minute set threshold for AdMod.
                Near end access: read-write
                Far end access: No access
                "
            ::= { xfRLPMAMConfigEntry 1 }

        xfPMAMSetThreshold24h OBJECT-TYPE
            SYNTAX Integer32
            MAX-ACCESS read-write
            STATUS current
            DESCRIPTION
                "The 24 hour set threshold for AdMod.
                Near end access: read-write
                Far end access: No access
                "
            ::= { xfRLPMAMConfigEntry 2 }

        xfPMAMResetThreshold15m OBJECT-TYPE
            SYNTAX Integer32
            MAX-ACCESS read-write
            STATUS current
            DESCRIPTION
                "The 15 minute reset threshold for AdMod.
                Near end access: read-write
                Far end access: No access
                "
            ::= { xfRLPMAMConfigEntry 3 }

        xfPMAMStatus OBJECT-TYPE
            SYNTAX BITS
            {
                am15m1(0),
                am15m2(1),
                am15m3(2),

                am24h1(3),
                am24h2(4),
                am24h3(5)
            }
            MAX-ACCESS read-only
            STATUS current
            DESCRIPTION
                "Threshold alarm status"
            ::= { xfRLPMAMConfigEntry 4 }

        xfPMAMValidData OBJECT-TYPE
            SYNTAX BITS
            {
                valid15m4QAM(0),
                valid15m8QAM(1),
                valid15m16QAM(2),
                valid15m32QAM(3),
                valid15m64QAM(4),
                valid15m128QAM(5),
                valid15m256QAM(6),
                valid15m512QAM(7),
                valid15m1024QAM(8)
            }
            MAX-ACCESS read-only
            STATUS current
            DESCRIPTION
                "It reports which modulation's PM data that are valid."
            ::= { xfRLPMAMConfigEntry 5 }

------------------------------------------------------------------------------
-- xfRLPMAMCurrent24hTable
------------------------------------------------------------------------------

        xfRLPMAMCurrent24hTable OBJECT-TYPE
            SYNTAX SEQUENCE OF XfRLPMAMCurrent24hEntry
            MAX-ACCESS not-accessible
            STATUS current
            DESCRIPTION
                "TBD"
            ::= { xfRadioLinkPtpTerminalObjects 17 }

        xfRLPMAMCurrent24hEntry OBJECT-TYPE
            SYNTAX XfRLPMAMCurrent24hEntry
            MAX-ACCESS not-accessible
            STATUS current
            DESCRIPTION
                "Entry in the xfRLPMAMCurrent24hTable."
            INDEX { ifIndex }
            ::= { xfRLPMAMCurrent24hTable 1 }

        XfRLPMAMCurrent24hEntry ::=
            SEQUENCE {
                xfPMAMCurrent24h4QAM
                    PerfCurrentCount,
                xfPMAMCurrent24h8QAM
                    PerfCurrentCount,
                xfPMAMCurrent24h16QAM
                    PerfCurrentCount,
                xfPMAMCurrent24h32QAM
                    PerfCurrentCount,
                xfPMAMCurrent24h64QAM
                    PerfCurrentCount,
                xfPMAMCurrent24h128QAM
                    PerfCurrentCount,
                xfPMAMCurrent24h256QAM
                    PerfCurrentCount,
                xfPMAMCurrent24h512QAM
                    PerfCurrentCount,
                xfPMAMCurrent24h1024QAM
                    PerfCurrentCount,
                xfPMAMCurrent24h4QAMEnRLB
                    PerfCurrentCount,
                xfPMAMCurrent24h8QAMEnRLB
                    PerfCurrentCount,
                xfPMAMCurrent24h16QAMEnRLB
                    PerfCurrentCount,
                xfPMAMCurrent24h32QAMEnRLB
                    PerfCurrentCount,
                xfPMAMCurrent24h64QAMEnRLB
                    PerfCurrentCount,
                xfPMAMCurrent24h128QAMEnRLB
                    PerfCurrentCount,
                xfPMAMCurrent24h256QAMEnRLB
                    PerfCurrentCount,
                xfPMAMCurrent24h512QAMEnRLB
                    PerfCurrentCount,
                xfPMAMCurrent24h1024QAMEnRLB
                    PerfCurrentCount
             }
--
-- The xfRLPMAMCurrent24hTable MOs
--

        xfPMAMCurrent24h4QAM OBJECT-TYPE
            SYNTAX PerfCurrentCount
            MAX-ACCESS read-only
            STATUS current
            DESCRIPTION
                "Valid time since reset"
            ::= { xfRLPMAMCurrent24hEntry 1 }

       xfPMAMCurrent24h8QAM OBJECT-TYPE
            SYNTAX PerfCurrentCount
            MAX-ACCESS read-only
            STATUS current
            DESCRIPTION
                "Valid time since reset"
            ::= { xfRLPMAMCurrent24hEntry 2 }

        xfPMAMCurrent24h16QAM OBJECT-TYPE
            SYNTAX PerfCurrentCount
            MAX-ACCESS read-only
            STATUS current
            DESCRIPTION
                "Valid time since reset"
            ::= { xfRLPMAMCurrent24hEntry 3 }

        xfPMAMCurrent24h32QAM OBJECT-TYPE
            SYNTAX PerfCurrentCount
            MAX-ACCESS read-only
            STATUS current
            DESCRIPTION
                "Valid time since reset"
            ::= { xfRLPMAMCurrent24hEntry 4 }

       xfPMAMCurrent24h64QAM OBJECT-TYPE
            SYNTAX PerfCurrentCount
            MAX-ACCESS read-only
            STATUS current
            DESCRIPTION
                "Valid time since reset"
            ::= { xfRLPMAMCurrent24hEntry 5 }

        xfPMAMCurrent24h128QAM OBJECT-TYPE
            SYNTAX PerfCurrentCount
            MAX-ACCESS read-only
            STATUS current
            DESCRIPTION
                "Valid time since reset"
            ::= { xfRLPMAMCurrent24hEntry 6 }

        xfPMAMCurrent24h256QAM OBJECT-TYPE
            SYNTAX PerfCurrentCount
            MAX-ACCESS read-only
            STATUS current
            DESCRIPTION
                "Valid time since reset"
            ::= { xfRLPMAMCurrent24hEntry 7 }

        xfPMAMCurrent24h512QAM OBJECT-TYPE
            SYNTAX PerfCurrentCount
            MAX-ACCESS read-only
            STATUS current
            DESCRIPTION
                "Valid time since reset"
            ::= { xfRLPMAMCurrent24hEntry 8 }

        xfPMAMCurrent24h1024QAM OBJECT-TYPE
            SYNTAX PerfCurrentCount
            MAX-ACCESS read-only
            STATUS current
            DESCRIPTION
                "Valid time since reset"
            ::= { xfRLPMAMCurrent24hEntry 9 }

        xfPMAMCurrent24h4QAMEnRLB OBJECT-TYPE
            SYNTAX PerfCurrentCount
            MAX-ACCESS read-only
            STATUS current
            DESCRIPTION
                "Valid time since reset"
            ::= { xfRLPMAMCurrent24hEntry 10 }

       xfPMAMCurrent24h8QAMEnRLB OBJECT-TYPE
            SYNTAX PerfCurrentCount
            MAX-ACCESS read-only
            STATUS current
            DESCRIPTION
                "Valid time since reset"
            ::= { xfRLPMAMCurrent24hEntry 11 }

        xfPMAMCurrent24h16QAMEnRLB OBJECT-TYPE
            SYNTAX PerfCurrentCount
            MAX-ACCESS read-only
            STATUS current
            DESCRIPTION
                "Valid time since reset"
            ::= { xfRLPMAMCurrent24hEntry 12 }

        xfPMAMCurrent24h32QAMEnRLB OBJECT-TYPE
            SYNTAX PerfCurrentCount
            MAX-ACCESS read-only
            STATUS current
            DESCRIPTION
                "Valid time since reset"
            ::= { xfRLPMAMCurrent24hEntry 13 }

       xfPMAMCurrent24h64QAMEnRLB OBJECT-TYPE
            SYNTAX PerfCurrentCount
            MAX-ACCESS read-only
            STATUS current
            DESCRIPTION
                "Valid time since reset"
            ::= { xfRLPMAMCurrent24hEntry 14 }

        xfPMAMCurrent24h128QAMEnRLB OBJECT-TYPE
            SYNTAX PerfCurrentCount
            MAX-ACCESS read-only
            STATUS current
            DESCRIPTION
                "Valid time since reset"
            ::= { xfRLPMAMCurrent24hEntry 15 }

        xfPMAMCurrent24h256QAMEnRLB OBJECT-TYPE
            SYNTAX PerfCurrentCount
            MAX-ACCESS read-only
            STATUS current
            DESCRIPTION
                "Valid time since reset"
            ::= { xfRLPMAMCurrent24hEntry 16 }

        xfPMAMCurrent24h512QAMEnRLB OBJECT-TYPE
            SYNTAX PerfCurrentCount
            MAX-ACCESS read-only
            STATUS current
            DESCRIPTION
                "Valid time since reset"
            ::= { xfRLPMAMCurrent24hEntry 17 }

        xfPMAMCurrent24h1024QAMEnRLB OBJECT-TYPE
            SYNTAX PerfCurrentCount
            MAX-ACCESS read-only
            STATUS current
            DESCRIPTION
                "Valid time since reset"
            ::= { xfRLPMAMCurrent24hEntry 18 }

------------------------------------------------------------------------------
-- xfRLPMAMInterval24hTable
------------------------------------------------------------------------------

        xfRLPMAMInterval24hTable OBJECT-TYPE
            SYNTAX SEQUENCE OF XfRLPMAMInterval24hEntry
            MAX-ACCESS not-accessible
            STATUS current
            DESCRIPTION
                "TBD"
            ::= { xfRadioLinkPtpTerminalObjects 18 }

        xfRLPMAMInterval24hEntry OBJECT-TYPE
            SYNTAX XfRLPMAMInterval24hEntry
            MAX-ACCESS not-accessible
            STATUS current
            DESCRIPTION
                "Entry in the xfRLPMAMInterval24hTable."
            INDEX { ifIndex }
            ::= { xfRLPMAMInterval24hTable 1 }

        XfRLPMAMInterval24hEntry ::=
            SEQUENCE {
                xfPMAMInterval24h4QAM
                    PerfIntervalCount,
                xfPMAMInterval24h8QAM
                    PerfIntervalCount,
                xfPMAMInterval24h16QAM
                    PerfIntervalCount,
                xfPMAMInterval24h32QAM
                    PerfIntervalCount,
                xfPMAMInterval24h64QAM
                    PerfIntervalCount,
                xfPMAMInterval24h128QAM
                    PerfIntervalCount,
                xfPMAMInterval24h256QAM
                    PerfIntervalCount,
                xfPMAMInterval24h512QAM
                    PerfIntervalCount,
                xfPMAMInterval24hValidData
                    TruthValue,
                xfPMAMInterval24h1024QAM
                    PerfIntervalCount,
                xfPMAMInterval24h4QAMEnRLB
                    PerfIntervalCount,
                xfPMAMInterval24h8QAMEnRLB
                    PerfIntervalCount,
                xfPMAMInterval24h16QAMEnRLB
                    PerfIntervalCount,
                xfPMAMInterval24h32QAMEnRLB
                    PerfIntervalCount,
                xfPMAMInterval24h64QAMEnRLB
                    PerfIntervalCount,
                xfPMAMInterval24h128QAMEnRLB
                    PerfIntervalCount,
                xfPMAMInterval24h256QAMEnRLB
                    PerfIntervalCount,
                xfPMAMInterval24h512QAMEnRLB
                    PerfIntervalCount,
                xfPMAMInterval24h1024QAMEnRLB
                    PerfIntervalCount
             }

--
-- The xfRLPMAMInterval24hTable MOs
--

        xfPMAMInterval24h4QAM OBJECT-TYPE
            SYNTAX PerfIntervalCount
            MAX-ACCESS read-only
            STATUS current
            DESCRIPTION
                "Interval count."
            ::= { xfRLPMAMInterval24hEntry 1 }

        xfPMAMInterval24h8QAM OBJECT-TYPE
            SYNTAX PerfIntervalCount
            MAX-ACCESS read-only
            STATUS current
            DESCRIPTION
                "Interval count."
            ::= { xfRLPMAMInterval24hEntry 2 }

        xfPMAMInterval24h16QAM OBJECT-TYPE
            SYNTAX PerfIntervalCount
            MAX-ACCESS read-only
            STATUS current
            DESCRIPTION
                "Interval count."
            ::= { xfRLPMAMInterval24hEntry 3 }

        xfPMAMInterval24h32QAM OBJECT-TYPE
            SYNTAX PerfIntervalCount
            MAX-ACCESS read-only
            STATUS current
            DESCRIPTION
                "Interval count."
            ::= { xfRLPMAMInterval24hEntry 4 }

        xfPMAMInterval24h64QAM OBJECT-TYPE
            SYNTAX PerfIntervalCount
            MAX-ACCESS read-only
            STATUS current
            DESCRIPTION
                "Interval count."
            ::= { xfRLPMAMInterval24hEntry 5 }

        xfPMAMInterval24h128QAM OBJECT-TYPE
            SYNTAX PerfIntervalCount
            MAX-ACCESS read-only
            STATUS current
            DESCRIPTION
                "Interval count."
            ::= { xfRLPMAMInterval24hEntry 6 }

        xfPMAMInterval24h256QAM OBJECT-TYPE
            SYNTAX PerfIntervalCount
            MAX-ACCESS read-only
            STATUS current
            DESCRIPTION
                "Interval count."
            ::= { xfRLPMAMInterval24hEntry 7 }

        xfPMAMInterval24h512QAM OBJECT-TYPE
            SYNTAX PerfIntervalCount
            MAX-ACCESS read-only
            STATUS current
            DESCRIPTION
                "Interval count."
            ::= { xfRLPMAMInterval24hEntry 8 }

        xfPMAMInterval24hValidData OBJECT-TYPE
            SYNTAX TruthValue
            MAX-ACCESS read-only
            STATUS current
            DESCRIPTION
                "This variable indicates whether the data
                for this interval is valid."
            ::= { xfRLPMAMInterval24hEntry 9 }

        xfPMAMInterval24h1024QAM OBJECT-TYPE
            SYNTAX PerfIntervalCount
            MAX-ACCESS read-only
            STATUS current
            DESCRIPTION
                "Interval count."
            ::= { xfRLPMAMInterval24hEntry 10 }

        xfPMAMInterval24h4QAMEnRLB OBJECT-TYPE
            SYNTAX PerfIntervalCount
            MAX-ACCESS read-only
            STATUS current
            DESCRIPTION
                "Interval count."
            ::= { xfRLPMAMInterval24hEntry 11 }

         xfPMAMInterval24h8QAMEnRLB OBJECT-TYPE
            SYNTAX PerfIntervalCount
            MAX-ACCESS read-only
            STATUS current
            DESCRIPTION
                "Interval count."
            ::= { xfRLPMAMInterval24hEntry 12 }

        xfPMAMInterval24h16QAMEnRLB OBJECT-TYPE
            SYNTAX PerfIntervalCount
            MAX-ACCESS read-only
            STATUS current
            DESCRIPTION
                "Interval count."
            ::= { xfRLPMAMInterval24hEntry 13 }

        xfPMAMInterval24h32QAMEnRLB OBJECT-TYPE
            SYNTAX PerfIntervalCount
            MAX-ACCESS read-only
            STATUS current
            DESCRIPTION
                "Interval count."
            ::= { xfRLPMAMInterval24hEntry 14 }

        xfPMAMInterval24h64QAMEnRLB OBJECT-TYPE
            SYNTAX PerfIntervalCount
            MAX-ACCESS read-only
            STATUS current
            DESCRIPTION
                "Interval count."
            ::= { xfRLPMAMInterval24hEntry 15 }

        xfPMAMInterval24h128QAMEnRLB OBJECT-TYPE
            SYNTAX PerfIntervalCount
            MAX-ACCESS read-only
            STATUS current
            DESCRIPTION
                "Interval count."
            ::= { xfRLPMAMInterval24hEntry 16 }

        xfPMAMInterval24h256QAMEnRLB OBJECT-TYPE
            SYNTAX PerfIntervalCount
            MAX-ACCESS read-only
            STATUS current
            DESCRIPTION
                "Interval count."
            ::= { xfRLPMAMInterval24hEntry 17 }

        xfPMAMInterval24h512QAMEnRLB OBJECT-TYPE
            SYNTAX PerfIntervalCount
            MAX-ACCESS read-only
            STATUS current
            DESCRIPTION
                "Interval count."
            ::= { xfRLPMAMInterval24hEntry 18 }

        xfPMAMInterval24h1024QAMEnRLB OBJECT-TYPE
            SYNTAX PerfIntervalCount
            MAX-ACCESS read-only
            STATUS current
            DESCRIPTION
                "Interval count."
            ::= { xfRLPMAMInterval24hEntry 19 }

------------------------------------------------------------------------------
-- xfRLPMAMCurrent15mTable
------------------------------------------------------------------------------

        xfRLPMAMCurrent15mTable OBJECT-TYPE
            SYNTAX SEQUENCE OF XfRLPMAMCurrent15mEntry
            MAX-ACCESS not-accessible
            STATUS current
            DESCRIPTION
                "TBD"
            ::= { xfRadioLinkPtpTerminalObjects 19 }

        xfRLPMAMCurrent15mEntry OBJECT-TYPE
            SYNTAX XfRLPMAMCurrent15mEntry
            MAX-ACCESS not-accessible
            STATUS current
            DESCRIPTION
                "Entry in the table."
            INDEX { ifIndex }
            ::= { xfRLPMAMCurrent15mTable 1 }

        XfRLPMAMCurrent15mEntry ::=
            SEQUENCE {
                xfPMAMCurrent15m4QAM
                    PerfCurrentCount,
                xfPMAMCurrent15m8QAM
                    PerfCurrentCount,
                xfPMAMCurrent15m16QAM
                    PerfCurrentCount,
                xfPMAMCurrent15m32QAM
                    PerfCurrentCount,
                xfPMAMCurrent15m64QAM
                    PerfCurrentCount,
                xfPMAMCurrent15m128QAM
                    PerfCurrentCount,
                xfPMAMCurrent15m256QAM
                    PerfCurrentCount,
                xfPMAMCurrent15m512QAM
                    PerfCurrentCount,
                xfPMAMCurrent15m1024QAM
                    PerfCurrentCount,
                xfPMAMCurrent15m4QAMEnRLB
                    PerfCurrentCount,
                xfPMAMCurrent15m8QAMEnRLB
                    PerfCurrentCount,
                xfPMAMCurrent15m16QAMEnRLB
                    PerfCurrentCount,
                xfPMAMCurrent15m32QAMEnRLB
                    PerfCurrentCount,
                xfPMAMCurrent15m64QAMEnRLB
                    PerfCurrentCount,
                xfPMAMCurrent15m128QAMEnRLB
                    PerfCurrentCount,
                xfPMAMCurrent15m256QAMEnRLB
                    PerfCurrentCount,
                xfPMAMCurrent15m512QAMEnRLB
                    PerfCurrentCount,
                xfPMAMCurrent15m1024QAMEnRLB
                    PerfCurrentCount
             }

--
-- The xfRLPMAMCurrent15mTable MOs
--
        xfPMAMCurrent15m4QAM OBJECT-TYPE
            SYNTAX PerfCurrentCount
            MAX-ACCESS read-only
            STATUS current
            DESCRIPTION
                "Valid interval time since reset.
                "
            ::= { xfRLPMAMCurrent15mEntry 1 }

        xfPMAMCurrent15m8QAM OBJECT-TYPE
            SYNTAX PerfCurrentCount
            MAX-ACCESS read-only
            STATUS current
            DESCRIPTION
                "Valid interval time since reset.
                "
            ::= { xfRLPMAMCurrent15mEntry 2 }

        xfPMAMCurrent15m16QAM OBJECT-TYPE
            SYNTAX PerfCurrentCount
            MAX-ACCESS read-only
            STATUS current
            DESCRIPTION
                "Valid interval time since reset.
                "
            ::= { xfRLPMAMCurrent15mEntry 3 }

        xfPMAMCurrent15m32QAM OBJECT-TYPE
            SYNTAX PerfCurrentCount
            MAX-ACCESS read-only
            STATUS current
            DESCRIPTION
                "Valid interval time since reset.
                "
            ::= { xfRLPMAMCurrent15mEntry 4 }

        xfPMAMCurrent15m64QAM OBJECT-TYPE
            SYNTAX PerfCurrentCount
            MAX-ACCESS read-only
            STATUS current
            DESCRIPTION
                "Valid interval time since reset.
                "
            ::= { xfRLPMAMCurrent15mEntry 5 }

        xfPMAMCurrent15m128QAM OBJECT-TYPE
            SYNTAX PerfCurrentCount
            MAX-ACCESS read-only
            STATUS current
            DESCRIPTION
                "Valid interval time since reset.
                "
            ::= { xfRLPMAMCurrent15mEntry 6 }

        xfPMAMCurrent15m256QAM OBJECT-TYPE
            SYNTAX PerfCurrentCount
            MAX-ACCESS read-only
            STATUS current
            DESCRIPTION
                "Valid interval time since reset.
                "
            ::= { xfRLPMAMCurrent15mEntry 7 }

        xfPMAMCurrent15m512QAM OBJECT-TYPE
            SYNTAX PerfCurrentCount
            MAX-ACCESS read-only
            STATUS current
            DESCRIPTION
                "Valid interval time since reset.
                "
            ::= { xfRLPMAMCurrent15mEntry 8 }

        xfPMAMCurrent15m1024QAM OBJECT-TYPE
            SYNTAX PerfCurrentCount
            MAX-ACCESS read-only
            STATUS current
            DESCRIPTION
                "Valid interval time since reset.
                "
            ::= { xfRLPMAMCurrent15mEntry 9 }

        xfPMAMCurrent15m4QAMEnRLB OBJECT-TYPE
            SYNTAX PerfCurrentCount
            MAX-ACCESS read-only
            STATUS current
            DESCRIPTION
                "Valid interval time since reset.
                "
            ::= { xfRLPMAMCurrent15mEntry 10 }

        xfPMAMCurrent15m8QAMEnRLB OBJECT-TYPE
            SYNTAX PerfCurrentCount
            MAX-ACCESS read-only
            STATUS current
            DESCRIPTION
                "Valid interval time since reset.
                "
            ::= { xfRLPMAMCurrent15mEntry 11 }

        xfPMAMCurrent15m16QAMEnRLB OBJECT-TYPE
            SYNTAX PerfCurrentCount
            MAX-ACCESS read-only
            STATUS current
            DESCRIPTION
                "Valid interval time since reset.
                "
            ::= { xfRLPMAMCurrent15mEntry 12 }

        xfPMAMCurrent15m32QAMEnRLB OBJECT-TYPE
            SYNTAX PerfCurrentCount
            MAX-ACCESS read-only
            STATUS current
            DESCRIPTION
                "Valid interval time since reset.
                "
            ::= { xfRLPMAMCurrent15mEntry 13 }

        xfPMAMCurrent15m64QAMEnRLB OBJECT-TYPE
            SYNTAX PerfCurrentCount
            MAX-ACCESS read-only
            STATUS current
            DESCRIPTION
                "Valid interval time since reset.
                "
            ::= { xfRLPMAMCurrent15mEntry 14 }

        xfPMAMCurrent15m128QAMEnRLB OBJECT-TYPE
            SYNTAX PerfCurrentCount
            MAX-ACCESS read-only
            STATUS current
            DESCRIPTION
                "Valid interval time since reset.
                "
            ::= { xfRLPMAMCurrent15mEntry 15 }

        xfPMAMCurrent15m256QAMEnRLB OBJECT-TYPE
            SYNTAX PerfCurrentCount
            MAX-ACCESS read-only
            STATUS current
            DESCRIPTION
                "Valid interval time since reset.
                "
            ::= { xfRLPMAMCurrent15mEntry 16 }

        xfPMAMCurrent15m512QAMEnRLB OBJECT-TYPE
            SYNTAX PerfCurrentCount
            MAX-ACCESS read-only
            STATUS current
            DESCRIPTION
                "Valid interval time since reset.
                "
            ::= { xfRLPMAMCurrent15mEntry 17 }

        xfPMAMCurrent15m1024QAMEnRLB OBJECT-TYPE
            SYNTAX PerfCurrentCount
            MAX-ACCESS read-only
            STATUS current
            DESCRIPTION
                "Valid interval time since reset.
                "
            ::= { xfRLPMAMCurrent15mEntry 18 }

------------------------------------------------------------------------------
-- xfRLPMAMInterval15mTable
------------------------------------------------------------------------------

        xfRLPMAMInterval15mTable OBJECT-TYPE
            SYNTAX SEQUENCE OF XfRLPMAMInterval15mEntry
            MAX-ACCESS not-accessible
            STATUS current
            DESCRIPTION
                "TBD"
            ::= { xfRadioLinkPtpTerminalObjects 20 }

        xfRLPMAMInterval15mEntry OBJECT-TYPE
            SYNTAX XfRLPMAMInterval15mEntry
            MAX-ACCESS not-accessible
            STATUS current
            DESCRIPTION
                "Entry in the table."
            INDEX { ifIndex, xfPMAMInterval15mIntervalNumber }
            ::= { xfRLPMAMInterval15mTable 1 }

        XfRLPMAMInterval15mEntry ::=
            SEQUENCE {
                xfPMAMInterval15mIntervalNumber
                    Integer32,
                xfPMAMInterval15m4QAM
                    PerfIntervalCount,
                xfPMAMInterval15m8QAM
                    PerfIntervalCount,
                xfPMAMInterval15m16QAM
                    PerfIntervalCount,
                xfPMAMInterval15m32QAM
                    PerfIntervalCount,
                xfPMAMInterval15m64QAM
                    PerfIntervalCount,
                xfPMAMInterval15m128QAM
                    PerfIntervalCount,
                xfPMAMInterval15m256QAM
                    PerfIntervalCount,
                xfPMAMInterval15m512QAM
                    PerfIntervalCount,
                xfPMAMInterval15mValidData
                    TruthValue,
                xfPMAMInterval15m1024QAM
                    PerfIntervalCount,
                xfPMAMInterval15m4QAMEnRLB
                    PerfIntervalCount,
                xfPMAMInterval15m8QAMEnRLB
                    PerfIntervalCount,
                xfPMAMInterval15m16QAMEnRLB
                    PerfIntervalCount,
                xfPMAMInterval15m32QAMEnRLB
                    PerfIntervalCount,
                xfPMAMInterval15m64QAMEnRLB
                    PerfIntervalCount,
                xfPMAMInterval15m128QAMEnRLB
                    PerfIntervalCount,
                xfPMAMInterval15m256QAMEnRLB
                    PerfIntervalCount,
                xfPMAMInterval15m512QAMEnRLB
                    PerfIntervalCount,
                xfPMAMInterval15m1024QAMEnRLB
                    PerfIntervalCount
      }

--
-- The xfRLPMAMInterval15mTable MOs
--
        xfPMAMInterval15mIntervalNumber OBJECT-TYPE
            SYNTAX Integer32 (1..96)
            MAX-ACCESS read-only
            STATUS current
            DESCRIPTION
                "A number between 1 and 96, which identifies the interval for which
                the set of statistics is available. The interval identified by 1
                is the most recently completed 15 minute interval, and the interval
                identified by N is the interval immediately preceding the one
                identified by N-1."
            ::= { xfRLPMAMInterval15mEntry 1 }

        xfPMAMInterval15m4QAM OBJECT-TYPE
            SYNTAX PerfIntervalCount
            MAX-ACCESS read-only
            STATUS current
            DESCRIPTION
                "Interval count."
            ::= { xfRLPMAMInterval15mEntry 2 }

         xfPMAMInterval15m8QAM OBJECT-TYPE
            SYNTAX PerfIntervalCount
            MAX-ACCESS read-only
            STATUS current
            DESCRIPTION
                "Interval count."
            ::= { xfRLPMAMInterval15mEntry 3 }

         xfPMAMInterval15m16QAM OBJECT-TYPE
            SYNTAX PerfIntervalCount
            MAX-ACCESS read-only
            STATUS current
            DESCRIPTION
                "Interval count."
            ::= { xfRLPMAMInterval15mEntry 4 }

         xfPMAMInterval15m32QAM OBJECT-TYPE
            SYNTAX PerfIntervalCount
            MAX-ACCESS read-only
            STATUS current
            DESCRIPTION
                "Interval count."
            ::= { xfRLPMAMInterval15mEntry 5 }

         xfPMAMInterval15m64QAM OBJECT-TYPE
            SYNTAX PerfIntervalCount
            MAX-ACCESS read-only
            STATUS current
            DESCRIPTION
                "Interval count."
            ::= { xfRLPMAMInterval15mEntry 6 }

         xfPMAMInterval15m128QAM OBJECT-TYPE
            SYNTAX PerfIntervalCount
            MAX-ACCESS read-only
            STATUS current
            DESCRIPTION
                "Interval count."
            ::= { xfRLPMAMInterval15mEntry 7 }

         xfPMAMInterval15m256QAM OBJECT-TYPE
            SYNTAX PerfIntervalCount
            MAX-ACCESS read-only
            STATUS current
            DESCRIPTION
                "Interval count."
            ::= { xfRLPMAMInterval15mEntry 8 }

          xfPMAMInterval15m512QAM OBJECT-TYPE
            SYNTAX PerfIntervalCount
            MAX-ACCESS read-only
            STATUS current
            DESCRIPTION
                "Interval count."
            ::= { xfRLPMAMInterval15mEntry 9 }

        xfPMAMInterval15mValidData OBJECT-TYPE
            SYNTAX TruthValue
            MAX-ACCESS read-only
            STATUS current
            DESCRIPTION
                 "This variable indicates whether the data
                for this interval is valid."
            ::= { xfRLPMAMInterval15mEntry 10 }

        xfPMAMInterval15m1024QAM OBJECT-TYPE
            SYNTAX PerfIntervalCount
            MAX-ACCESS read-only
            STATUS current
            DESCRIPTION
                "Interval count."
            ::= { xfRLPMAMInterval15mEntry 11 }

        xfPMAMInterval15m4QAMEnRLB OBJECT-TYPE
            SYNTAX PerfIntervalCount
            MAX-ACCESS read-only
            STATUS current
            DESCRIPTION
                "Interval count."
            ::= { xfRLPMAMInterval15mEntry 12 }

         xfPMAMInterval15m8QAMEnRLB OBJECT-TYPE
            SYNTAX PerfIntervalCount
            MAX-ACCESS read-only
            STATUS current
            DESCRIPTION
                "Interval count."
            ::= { xfRLPMAMInterval15mEntry 13 }

         xfPMAMInterval15m16QAMEnRLB OBJECT-TYPE
            SYNTAX PerfIntervalCount
            MAX-ACCESS read-only
            STATUS current
            DESCRIPTION
                "Interval count."
            ::= { xfRLPMAMInterval15mEntry 14 }

         xfPMAMInterval15m32QAMEnRLB OBJECT-TYPE
            SYNTAX PerfIntervalCount
            MAX-ACCESS read-only
            STATUS current
            DESCRIPTION
                "Interval count."
            ::= { xfRLPMAMInterval15mEntry 15 }

         xfPMAMInterval15m64QAMEnRLB OBJECT-TYPE
            SYNTAX PerfIntervalCount
            MAX-ACCESS read-only
            STATUS current
            DESCRIPTION
                "Interval count."
            ::= { xfRLPMAMInterval15mEntry 16 }

         xfPMAMInterval15m128QAMEnRLB OBJECT-TYPE
            SYNTAX PerfIntervalCount
            MAX-ACCESS read-only
            STATUS current
            DESCRIPTION
                "Interval count."
            ::= { xfRLPMAMInterval15mEntry 17 }

         xfPMAMInterval15m256QAMEnRLB OBJECT-TYPE
            SYNTAX PerfIntervalCount
            MAX-ACCESS read-only
            STATUS current
            DESCRIPTION
                "Interval count."
            ::= { xfRLPMAMInterval15mEntry 18 }

          xfPMAMInterval15m512QAMEnRLB OBJECT-TYPE
            SYNTAX PerfIntervalCount
            MAX-ACCESS read-only
            STATUS current
            DESCRIPTION
                "Interval count."
            ::= { xfRLPMAMInterval15mEntry 19 }

        xfPMAMInterval15m1024QAMEnRLB OBJECT-TYPE
            SYNTAX PerfIntervalCount
            MAX-ACCESS read-only
            STATUS current
            DESCRIPTION
                "Interval count."
            ::= { xfRLPMAMInterval15mEntry 20 }

------------------------------------------------------------------------------
-- xfRLPtpTerminalCapacityLicenseTable
------------------------------------------------------------------------------

        xfRLPtpTerminalCapacityLicenseTable OBJECT-TYPE
            SYNTAX SEQUENCE OF XfRLPtpTerminalCapacityLicenseEntry
            MAX-ACCESS not-accessible
            STATUS current
            DESCRIPTION
                "TBD"
            ::= { xfRadioLinkPtpTerminalObjects 21 }

        xfRLPtpTerminalCapacityLicenseEntry OBJECT-TYPE
            SYNTAX XfRLPtpTerminalCapacityLicenseEntry
            MAX-ACCESS not-accessible
            STATUS current
            DESCRIPTION
                "Entry in the table."
            INDEX { entLogicalIndex, xfTermRowIndex }
            ::= { xfRLPtpTerminalCapacityLicenseTable 1 }

        XfRLPtpTerminalCapacityLicenseEntry ::=
            SEQUENCE
            {
                xfTermCapacityLicenseRange           INTEGER,
                xfTermMaxCapacityRange         Integer32,
                xfTermMaxTribCapacityRange       Integer32
             }

--
-- The xfRLPtpTerminalCapacityLicenseTable MOs
--
        xfTermCapacityLicenseRange OBJECT-TYPE
            SYNTAX INTEGER
            {
              vr0(0),
              vr10(1),
              vr25(2),
              vr50(3),
              vr100(4),
              vr15(5),
              vr30(6),
              vr60(7),
              vr125(8),
              vr200(9),
              vr350(10),
              vr4(11),
              vr500(12),
              vr150(13),
              vr250(14),
              vr300(15),
              vr400(16),
              vr450(17)
             }
            MAX-ACCESS read-only
            STATUS current
            DESCRIPTION
                "xfTermCapacityLicenseRange"
            ::= { xfRLPtpTerminalCapacityLicenseEntry 1 }

        xfTermMaxCapacityRange OBJECT-TYPE
            SYNTAX Integer32
            MAX-ACCESS read-only
            STATUS current
            DESCRIPTION
                "TermMaxCapacityRange"
            ::= { xfRLPtpTerminalCapacityLicenseEntry 2 }

         xfTermMaxTribCapacityRange OBJECT-TYPE
            SYNTAX Integer32
            MAX-ACCESS read-only
            STATUS current
            DESCRIPTION
                "xfTermMaxTribCapacityRange"
            ::= { xfRLPtpTerminalCapacityLicenseEntry 3 }

------------------------------------------------------------------------------
-- xfRLPMSDCGainCurrent15mTable
------------------------------------------------------------------------------

  xfRLPMSDCGainCurrent15mTable OBJECT-TYPE
    SYNTAX SEQUENCE OF XfRLPMSDCGainCurrent15mEntry
    MAX-ACCESS not-accessible
    STATUS current
    DESCRIPTION
      "
      This table monitors the time spent in each SDC gain value in the current 15 minute period.
      "
    ::= { xfRadioLinkPtpTerminalObjects 22 }

  xfRLPMSDCGainCurrent15mEntry OBJECT-TYPE
    SYNTAX XfRLPMSDCGainCurrent15mEntry
    MAX-ACCESS not-accessible
    STATUS current
    DESCRIPTION
      "
      Entry in xfRLPMSDCGainCurrent15mTable.
      "
    INDEX { ifIndex }
    ::= { xfRLPMSDCGainCurrent15mTable 1 }

  XfRLPMSDCGainCurrent15mEntry ::=
    SEQUENCE
    {
      xfPMSDCGainCurrent15m0005dB
        PerfCurrentCount,
      xfPMSDCGainCurrent15m0510dB
        PerfCurrentCount,
      xfPMSDCGainCurrent15m1015dB
        PerfCurrentCount,
      xfPMSDCGainCurrent15m1520dB
        PerfCurrentCount,
      xfPMSDCGainCurrent15m2025dB
        PerfCurrentCount,
      xfPMSDCGainCurrent15m2530dB
        PerfCurrentCount
      }

--
-- xfRLPMSDCGainCurrent15mTable MOs
--
  xfPMSDCGainCurrent15m0005dB OBJECT-TYPE
    SYNTAX PerfCurrentCount
    MAX-ACCESS read-only
    STATUS current
    DESCRIPTION
      "
      The number of seconds the SDC gain has been in the range: (0.0 <= SdcGain < 0.5) dB.
      "
    ::= { xfRLPMSDCGainCurrent15mEntry 1 }

  xfPMSDCGainCurrent15m0510dB OBJECT-TYPE
    SYNTAX PerfCurrentCount
    MAX-ACCESS read-only
    STATUS current
    DESCRIPTION
      "
      The number of seconds the SDC gain has been in the range: (0.5 <= SdcGain < 1.0) dB.
      "
    ::= { xfRLPMSDCGainCurrent15mEntry 2 }

  xfPMSDCGainCurrent15m1015dB OBJECT-TYPE
    SYNTAX PerfCurrentCount
    MAX-ACCESS read-only
    STATUS current
    DESCRIPTION
      "
      The number of seconds the SDC gain has been in the range: (1.0 <= SdcGain < 1.5) dB.
      "
    ::= { xfRLPMSDCGainCurrent15mEntry 3 }

  xfPMSDCGainCurrent15m1520dB OBJECT-TYPE
    SYNTAX PerfCurrentCount
    MAX-ACCESS read-only
    STATUS current
    DESCRIPTION
      "
      The number of seconds the SDC gain has been in the range: (1.5 <= SdcGain < 2.0) dB.
      "
    ::= { xfRLPMSDCGainCurrent15mEntry 4 }

  xfPMSDCGainCurrent15m2025dB OBJECT-TYPE
    SYNTAX PerfCurrentCount
    MAX-ACCESS read-only
    STATUS current
    DESCRIPTION
      "
      The number of seconds the SDC gain has been in the range: (2.0 <= SdcGain < 2.5) dB.
      "
    ::= { xfRLPMSDCGainCurrent15mEntry 5 }

  xfPMSDCGainCurrent15m2530dB OBJECT-TYPE
    SYNTAX PerfCurrentCount
    MAX-ACCESS read-only
    STATUS current
    DESCRIPTION
      "
      The number of seconds the SDC gain has been in the range: (2.5 <= SdcGain < 3.0) dB.
      "
    ::= { xfRLPMSDCGainCurrent15mEntry 6 }

------------------------------------------------------------------------------
-- xfRLPMSDCGainInterval15mTable
------------------------------------------------------------------------------

  xfRLPMSDCGainInterval15mTable OBJECT-TYPE
    SYNTAX SEQUENCE OF XfRLPMSDCGainInterval15mEntry
    MAX-ACCESS not-accessible
    STATUS current
    DESCRIPTION
      "
      This table collects the time spent in each SDC gain value for the 15 minute intervals.
      "
    ::= { xfRadioLinkPtpTerminalObjects 23 }

  xfRLPMSDCGainInterval15mEntry OBJECT-TYPE
    SYNTAX XfRLPMSDCGainInterval15mEntry
    MAX-ACCESS not-accessible
    STATUS current
    DESCRIPTION
      "
      Entry in xfRLPMSDCGainInterval15mTable.
      "
    INDEX { ifIndex, xfPMSDCGainInterval15mIntervalNumber }
    ::= { xfRLPMSDCGainInterval15mTable 1 }

  XfRLPMSDCGainInterval15mEntry ::=
    SEQUENCE
    {
      xfPMSDCGainInterval15mIntervalNumber
        Integer32,
      xfPMSDCGainInterval15m0005dB
        PerfIntervalCount,
      xfPMSDCGainInterval15m0510dB
        PerfIntervalCount,
      xfPMSDCGainInterval15m1015dB
        PerfIntervalCount,
      xfPMSDCGainInterval15m1520dB
        PerfIntervalCount,
      xfPMSDCGainInterval15m2025dB
        PerfIntervalCount,
      xfPMSDCGainInterval15m2530dB
        PerfIntervalCount
    }

--
-- xfRLPMSDCGainInterval15mTable MOs
--
  xfPMSDCGainInterval15mIntervalNumber OBJECT-TYPE
    SYNTAX Integer32 (1..96)
    MAX-ACCESS read-only
    STATUS current
    DESCRIPTION
      "
      A number between 1 and 96, which identifies the interval for which the set of statistics is available.
      The interval identified by 1 is the most recently completed 15 minute interval, and the interval
      identified by N is the interval immediately preceding the one identified by N-1.
      "
    ::= { xfRLPMSDCGainInterval15mEntry 1 }

  xfPMSDCGainInterval15m0005dB OBJECT-TYPE
    SYNTAX PerfIntervalCount
    MAX-ACCESS read-only
    STATUS current
    DESCRIPTION
      "
      The number of seconds the SDC gain has been in the range: (0.0 <= SdcGain < 0.5) dB.
      "
    ::= { xfRLPMSDCGainInterval15mEntry 2 }

  xfPMSDCGainInterval15m0510dB OBJECT-TYPE
    SYNTAX PerfIntervalCount
    MAX-ACCESS read-only
    STATUS current
    DESCRIPTION
      "
      The number of seconds the SDC gain has been in the range: (0.5 <= SdcGain < 1.0) dB.
      "
    ::= { xfRLPMSDCGainInterval15mEntry 3 }

  xfPMSDCGainInterval15m1015dB OBJECT-TYPE
    SYNTAX PerfIntervalCount
    MAX-ACCESS read-only
    STATUS current
    DESCRIPTION
      "
      The number of seconds the SDC gain has been in the range: (1.0 <= SdcGain < 1.5) dB.
      "
    ::= { xfRLPMSDCGainInterval15mEntry 4 }

  xfPMSDCGainInterval15m1520dB OBJECT-TYPE
    SYNTAX PerfIntervalCount
    MAX-ACCESS read-only
    STATUS current
    DESCRIPTION
      "
      The number of seconds the SDC gain has been in the range: (1.5 <= SdcGain < 2.0) dB.
      "
    ::= { xfRLPMSDCGainInterval15mEntry 5 }

  xfPMSDCGainInterval15m2025dB OBJECT-TYPE
    SYNTAX PerfIntervalCount
    MAX-ACCESS read-only
    STATUS current
    DESCRIPTION
      "
      The number of seconds the SDC gain has been in the range: (2.0 <= SdcGain < 2.5) dB.
      "
    ::= { xfRLPMSDCGainInterval15mEntry 6 }

  xfPMSDCGainInterval15m2530dB OBJECT-TYPE
    SYNTAX PerfIntervalCount
    MAX-ACCESS read-only
    STATUS current
    DESCRIPTION
      "
      The number of seconds the SDC gain has been in the range: (2.5 <= SdcGain < 3.0) dB.
      "
    ::= { xfRLPMSDCGainInterval15mEntry 7 }

------------------------------------------------------------------------------
-- xfRLPMSDCGainCurrent24hTable
------------------------------------------------------------------------------

  xfRLPMSDCGainCurrent24hTable OBJECT-TYPE
    SYNTAX SEQUENCE OF XfRLPMSDCGainCurrent24hEntry
    MAX-ACCESS not-accessible
    STATUS current
    DESCRIPTION
      "
      This table monitors the time spent in each SDC gain value in the current 24 hours period.
      "
    ::= { xfRadioLinkPtpTerminalObjects 24 }

  xfRLPMSDCGainCurrent24hEntry OBJECT-TYPE
    SYNTAX XfRLPMSDCGainCurrent24hEntry
    MAX-ACCESS not-accessible
    STATUS current
    DESCRIPTION
      "
      Entry in xfRLPMSDCGainCurrent24hTable.
      "
    INDEX { ifIndex }
    ::= { xfRLPMSDCGainCurrent24hTable 1 }

  XfRLPMSDCGainCurrent24hEntry ::=
    SEQUENCE
    {
      xfPMSDCGainCurrent24h0005dB
        PerfCurrentCount,
      xfPMSDCGainCurrent24h0510dB
        PerfCurrentCount,
      xfPMSDCGainCurrent24h1015dB
        PerfCurrentCount,
      xfPMSDCGainCurrent24h1520dB
        PerfCurrentCount,
      xfPMSDCGainCurrent24h2025dB
        PerfCurrentCount,
      xfPMSDCGainCurrent24h2530dB
        PerfCurrentCount
      }

--
-- xfRLPMSDCGainCurrent24hTable MOs
--
  xfPMSDCGainCurrent24h0005dB OBJECT-TYPE
    SYNTAX PerfCurrentCount
    MAX-ACCESS read-only
    STATUS current
    DESCRIPTION
      "
      The number of seconds the SDC gain has been in the range: (0.0 <= SdcGain < 0.5) dB.
      "
    ::= { xfRLPMSDCGainCurrent24hEntry 1 }

  xfPMSDCGainCurrent24h0510dB OBJECT-TYPE
    SYNTAX PerfCurrentCount
    MAX-ACCESS read-only
    STATUS current
    DESCRIPTION
      "
      The number of seconds the SDC gain has been in the range: (0.5 <= SdcGain < 1.0) dB.
      "
    ::= { xfRLPMSDCGainCurrent24hEntry 2 }

  xfPMSDCGainCurrent24h1015dB OBJECT-TYPE
    SYNTAX PerfCurrentCount
    MAX-ACCESS read-only
    STATUS current
    DESCRIPTION
      "
      The number of seconds the SDC gain has been in the range: (1.0 <= SdcGain < 1.5) dB.
      "
    ::= { xfRLPMSDCGainCurrent24hEntry 3 }

  xfPMSDCGainCurrent24h1520dB OBJECT-TYPE
    SYNTAX PerfCurrentCount
    MAX-ACCESS read-only
    STATUS current
    DESCRIPTION
      "
      The number of seconds the SDC gain has been in the range: (1.5 <= SdcGain < 2.0) dB.
      "
    ::= { xfRLPMSDCGainCurrent24hEntry 4 }

  xfPMSDCGainCurrent24h2025dB OBJECT-TYPE
    SYNTAX PerfCurrentCount
    MAX-ACCESS read-only
    STATUS current
    DESCRIPTION
      "
      The number of seconds the SDC gain has been in the range: (2.0 <= SdcGain < 2.5) dB.
      "
    ::= { xfRLPMSDCGainCurrent24hEntry 5 }

  xfPMSDCGainCurrent24h2530dB OBJECT-TYPE
    SYNTAX PerfCurrentCount
    MAX-ACCESS read-only
    STATUS current
    DESCRIPTION
      "
      The number of seconds the SDC gain has been in the range: (2.5 <= SdcGain < 3.0) dB.
      "
    ::= { xfRLPMSDCGainCurrent24hEntry 6 }

------------------------------------------------------------------------------
-- xfRLPMSDCGainInterval24hTable
------------------------------------------------------------------------------

  xfRLPMSDCGainInterval24hTable OBJECT-TYPE
    SYNTAX SEQUENCE OF XfRLPMSDCGainInterval24hEntry
    MAX-ACCESS not-accessible
    STATUS current
    DESCRIPTION
      "
      This table collects the time spent in each SDC gain value for the 24 hours interval.
      "
    ::= { xfRadioLinkPtpTerminalObjects 25 }

  xfRLPMSDCGainInterval24hEntry OBJECT-TYPE
    SYNTAX XfRLPMSDCGainInterval24hEntry
    MAX-ACCESS not-accessible
    STATUS current
    DESCRIPTION
      "
      Entry in xfRLPMSDCGainInterval24hTable.
      "
    INDEX { ifIndex }
    ::= { xfRLPMSDCGainInterval24hTable 1 }

  XfRLPMSDCGainInterval24hEntry ::=
    SEQUENCE
    {
      xfPMSDCGainInterval24h0005dB
        PerfIntervalCount,
      xfPMSDCGainInterval24h0510dB
        PerfIntervalCount,
      xfPMSDCGainInterval24h1015dB
        PerfIntervalCount,
      xfPMSDCGainInterval24h1520dB
        PerfIntervalCount,
      xfPMSDCGainInterval24h2025dB
        PerfIntervalCount,
      xfPMSDCGainInterval24h2530dB
        PerfIntervalCount
    }

--
-- xfRLPMSDCGainInterval24hTable MOs
--

  xfPMSDCGainInterval24h0005dB OBJECT-TYPE
    SYNTAX PerfIntervalCount
    MAX-ACCESS read-only
    STATUS current
    DESCRIPTION
      "
      The number of seconds the SDC gain has been in the range: (0.0 <= SdcGain < 0.5) dB.
      "
    ::= { xfRLPMSDCGainInterval24hEntry 1 }

  xfPMSDCGainInterval24h0510dB OBJECT-TYPE
    SYNTAX PerfIntervalCount
    MAX-ACCESS read-only
    STATUS current
    DESCRIPTION
      "
      The number of seconds the SDC gain has been in the range: (0.5 <= SdcGain < 1.0) dB.
      "
    ::= { xfRLPMSDCGainInterval24hEntry 2 }

  xfPMSDCGainInterval24h1015dB OBJECT-TYPE
    SYNTAX PerfIntervalCount
    MAX-ACCESS read-only
    STATUS current
    DESCRIPTION
      "
      The number of seconds the SDC gain has been in the range: (1.0 <= SdcGain < 1.5) dB.
      "
    ::= { xfRLPMSDCGainInterval24hEntry 3 }

  xfPMSDCGainInterval24h1520dB OBJECT-TYPE
    SYNTAX PerfIntervalCount
    MAX-ACCESS read-only
    STATUS current
    DESCRIPTION
      "
      The number of seconds the SDC gain has been in the range: (1.5 <= SdcGain < 2.0) dB.
      "
    ::= { xfRLPMSDCGainInterval24hEntry 4 }

  xfPMSDCGainInterval24h2025dB OBJECT-TYPE
    SYNTAX PerfIntervalCount
    MAX-ACCESS read-only
    STATUS current
    DESCRIPTION
      "
      The number of seconds the SDC gain has been in the range: (2.0 <= SdcGain < 2.5) dB.
      "
    ::= { xfRLPMSDCGainInterval24hEntry 5 }

  xfPMSDCGainInterval24h2530dB OBJECT-TYPE
    SYNTAX PerfIntervalCount
    MAX-ACCESS read-only
    STATUS current
    DESCRIPTION
      "
      The number of seconds the SDC gain has been in the range: (2.5 <= SdcGain < 3.0) dB.
      "
    ::= { xfRLPMSDCGainInterval24hEntry 6 }

------------------------------------------------------------------------------
-- xfRLPMSDCGainConfigTable
------------------------------------------------------------------------------

  xfRLPMSDCGainConfigTable OBJECT-TYPE
    SYNTAX SEQUENCE OF XfRLPMSDCGainConfigEntry
    MAX-ACCESS not-accessible
    STATUS current
    DESCRIPTION
      "
      xfRLPMSDCGainConfigTable contains thresholds for setting and resetting alarms for SDC Gain PM data in SDC current and interval tables.
      "
    ::= { xfRadioLinkPtpTerminalObjects 26 }

  xfRLPMSDCGainConfigEntry OBJECT-TYPE
    SYNTAX XfRLPMSDCGainConfigEntry
    MAX-ACCESS not-accessible
    STATUS current
    DESCRIPTION
      "
      Entry in xfRLPMSDCGainConfigTable.
      "
    INDEX { ifIndex }
    ::= { xfRLPMSDCGainConfigTable 1 }

  XfRLPMSDCGainConfigEntry ::=
    SEQUENCE
    {
      xfPMSDCGainSetThreshold15m
        Integer32,
      xfPMSDCGainSetThreshold24h
        Integer32,
      xfPMSDCGainResetThreshold15m
        Integer32,
      xfPMSDCGainStatus
        BITS
    }

--
-- xfRLPMSDCGainConfigTable MOs
--

  xfPMSDCGainSetThreshold15m OBJECT-TYPE
    SYNTAX Integer32
    MAX-ACCESS read-write
    STATUS current
    DESCRIPTION
      "
      The 15 minute set threshold for the lowest SDC Gain interval: 0 - 0.5 dB.
      Default value is 180.
      "
  ::= { xfRLPMSDCGainConfigEntry 1 }

  xfPMSDCGainSetThreshold24h OBJECT-TYPE
    SYNTAX Integer32
    MAX-ACCESS read-write
    STATUS current
    DESCRIPTION
      "
      The 24 hour set threshold for the lowest SDC Gain interval: 0 - 0.5 dB.
      Default value is 1500.
      "
  ::= { xfRLPMSDCGainConfigEntry 2 }

  xfPMSDCGainResetThreshold15m OBJECT-TYPE
    SYNTAX Integer32
    MAX-ACCESS read-write
    STATUS current
    DESCRIPTION
      "
      The 15 minute reset threshold for the lowest SDC Gain interval: 0 - 0.5 dB.
      Default value is 20.
      "
  ::= { xfRLPMSDCGainConfigEntry 3 }

  xfPMSDCGainStatus OBJECT-TYPE
    SYNTAX BITS
    {
      sdcGain15m(0),
      sdcGain24h(1)
    }
  MAX-ACCESS read-only
  STATUS current
  DESCRIPTION
      "
      Threshold crossing SDC alarm status.
      "
  ::= { xfRLPMSDCGainConfigEntry 4 }

--
-- Extended Performance Tables --
--

--
-- xfRLExtRFPMConfigTable --
--

        xfRLExtRFPMConfigTable OBJECT-TYPE
            SYNTAX SEQUENCE OF XfRLExtRFPMConfigEntry
            MAX-ACCESS not-accessible
            STATUS current
            DESCRIPTION
                "This table contains the alarm threshold values for RL Extended RF PM.
                 Its index id the RF IF ifIndex."
            ::= { xfRadioLinkPtpTerminalObjects 27 }

        xfRLExtRFPMConfigEntry OBJECT-TYPE
            SYNTAX XfRLExtRFPMConfigEntry
            MAX-ACCESS not-accessible
            STATUS current
            DESCRIPTION
                "Entry in the xfRLExtRFPMConfigTable."
            INDEX { ifIndex } -- RF IF ifIndex
            ::= { xfRLExtRFPMConfigTable 1 }

        XfRLExtRFPMConfigEntry ::=
            SEQUENCE
            {
                xfExtRFPMRLTS1Threshold             Integer32,
                xfExtRFPMSetThreshold15mRLTS1       Integer32,
                xfExtRFPMResetThreshold15mRLTS1     Integer32,
                xfExtRFPMRLTS2Threshold             Integer32,
                xfExtRFPMSetThreshold15mRLTS2       Integer32,
                xfExtRFPMResetThreshold15mRLTS2     Integer32,
                xfExtRFPMSetThreshold15mRLTM        Integer32,
                xfExtRFPMResetThreshold15mRLTM      Integer32,
                xfExtRFPMTLTS1Threshold             Integer32,
                xfExtRFPMSetThreshold15mTLTS1       Integer32,
                xfExtRFPMResetThreshold15mTLTS1     Integer32,
                xfExtRFPMSetThreshold15mTLTM        Integer32,
                xfExtRFPMResetThreshold15mTLTM      Integer32,
                xfExtRFPMSetThreshold24hRLTS1       Integer32,
                xfExtRFPMSetThreshold24hRLTS2       Integer32,
                xfExtRFPMSetThreshold24hRLTM        Integer32,
                xfExtRFPMSetThreshold24hTLTS1       Integer32,
                xfExtRFPMSetThreshold24hTLTM        Integer32,
                xfExtRFPMStatus                     BITS,
                xfExtRFPMView                       INTEGER
            }

--
-- The xfRLExtRFPMConfigTable MOs
--
        xfExtRFPMRLTS1Threshold OBJECT-TYPE
            SYNTAX Integer32 (-999..-201)
            MAX-ACCESS read-write
            STATUS current
            DESCRIPTION
                "RLTS1 Alarm Threshold for Minimum RF Input Power.
                RF input level = value/10 dBm.
                Domain: [-99.9 ... -20.1 dBm]
                Valid for both 15 m & 24 h intervals.
                If changed current interval PM data must be reset.
                Always less than RLTS2, xfExtRFPMRLTS2Threshold."
            DEFVAL {-999}
            ::= { xfRLExtRFPMConfigEntry 1 }

        xfExtRFPMSetThreshold15mRLTS1 OBJECT-TYPE
            SYNTAX Integer32 (1..900)
            MAX-ACCESS read-write
            STATUS current
            DESCRIPTION
                "Received Level 1 Threshold Second (RLTS1) 15 minute.
                Alarm Set threshold in number of seconds that
                RF Input Power are allowed below the
                RLTS1 Alarm Threshold for Minimum RF Input Power
                in current 15 minute interval.
                Always greater than alarm Reset, xfExtRFPMResetThreshold15mRLTS1."
            DEFVAL {150}
            ::= { xfRLExtRFPMConfigEntry 2 }

        xfExtRFPMResetThreshold15mRLTS1 OBJECT-TYPE
            SYNTAX Integer32 (1..900)
            MAX-ACCESS read-write
            STATUS current
            DESCRIPTION
                "Received Level 1 Threshold Second (RLTS1) 15 minute.
                Alarm Reset threshold in number of seconds that
                RF Input Power are allowed below the
                RLTS1 Alarm Threshold for Minimum RF Input Power
                for entire current 15 minute interval.
                Always less than alarm Set, xfPMSetThreshold15mRLTS1."
            DEFVAL {1}
            ::= { xfRLExtRFPMConfigEntry 3 }

        xfExtRFPMRLTS2Threshold OBJECT-TYPE
            SYNTAX Integer32 (-998..-200)
            MAX-ACCESS read-write
            STATUS current
            DESCRIPTION
                "RLTS2 Alarm Threshold for Minimum RF Input Power.
                RF input level = value/10 dBm.
                Domain: [-99.8 ... -20.0 dBm]
                Valid for both 15 m & 24 h intervals.
                If changed current interval PM data must be reset.
                Always greater than RLTS1, xfExtRFPMRLTS1Threshold."
            DEFVAL {-998}
            ::= { xfRLExtRFPMConfigEntry 4 }

        xfExtRFPMSetThreshold15mRLTS2 OBJECT-TYPE
            SYNTAX Integer32 (1..900)
            MAX-ACCESS read-write
            STATUS current
            DESCRIPTION
                "Received Level 2 Threshold Second (RLTS2) 15 minute.
                Alarm Set threshold in number of seconds that
                RF Input Power are allowed below the
                RLTS2 Alarm Threshold for Minimum RF Input Power
                in current 15 minute interval.
                Always greater or equal to alarm Reset, xfExtRFPMResetThreshold15mRLTS2."
            DEFVAL {180}
            ::= { xfRLExtRFPMConfigEntry 5 }

        xfExtRFPMResetThreshold15mRLTS2 OBJECT-TYPE
            SYNTAX Integer32 (1..900)
            MAX-ACCESS read-write
            STATUS current
            DESCRIPTION
                "Received Level 2 Threshold Second (RLTS2) 15 minute.
                Alarm Reset threshold in number of seconds that
                RF Input Power are allowed below the
                RLTS2 Alarm Threshold for Minimum RF Input Power
                for entire current 15 minute interval.
                Always less or equal to alarm Set, xfExtRFPMSetThreshold15mRLTS2."
            DEFVAL {20}
            ::= { xfRLExtRFPMConfigEntry 6 }

        xfExtRFPMSetThreshold15mRLTM OBJECT-TYPE
            SYNTAX Integer32 (10..800)
            MAX-ACCESS read-write
            STATUS current
            DESCRIPTION
                "Receive Level Tide Mark (RLTM) 15 minute.
                Alarm Set threshold for maximum allowed
                max / min difference of RF Input Power
                in current 15 minute interval.
                RF input level = value/10 dB.
                Domain: [1.0 ... 80.0 dB]
                Always greater or equal to alarm Reset, xfExtRFPMResetThreshold15mRLTM."
            DEFVAL {800}
            ::= { xfRLExtRFPMConfigEntry 7 }

        xfExtRFPMResetThreshold15mRLTM OBJECT-TYPE
            SYNTAX Integer32 (10..800)
            MAX-ACCESS read-write
            STATUS current
            DESCRIPTION
                "Receive Level Tide Mark (RLTM) 15 minute.
                Alarm Reset threshold for maximum allowed
                max / min difference of RF Input Power
                for entire current 15 minute interval.
                RF input level = value/10 dB.
                Domain: [1.0 ... 80.0 dB]
                Always less or equal to alarm Set, xfExtRFPMSetThreshold15mRLTM."
            DEFVAL {790}
            ::= { xfRLExtRFPMConfigEntry 8 }

        xfExtRFPMTLTS1Threshold OBJECT-TYPE
            SYNTAX Integer32 (-100..45)
            MAX-ACCESS read-write
            STATUS current
            DESCRIPTION
                "TLTS1 Alarm Threshold for Maximum RF Output Power.
                RF output level = value dBm.
                Domain: [-100 ... 45 dBm]
                Valid for both 15 m & 24 h intervals.
                If changed current interval PM data must be reset."
            DEFVAL {45}
            ::= { xfRLExtRFPMConfigEntry 9 }

        xfExtRFPMSetThreshold15mTLTS1 OBJECT-TYPE
            SYNTAX Integer32 (1..900)
            MAX-ACCESS read-write
            STATUS current
            DESCRIPTION
                "Transmitted Levels 1 Threshold Second (TLTS1) 15 minute.
                Alarm Set threshold in number of seconds that
                RF Output Power are allowed above the
                TLTS1 Alarm Threshold for Maximum RF Output Power
                in current 15 minute interval.
                Always greater or equal to alarm Reset, xfExtRFPMResetThreshold15mTLTS1."
            DEFVAL {180}
            ::= { xfRLExtRFPMConfigEntry 10 }

        xfExtRFPMResetThreshold15mTLTS1 OBJECT-TYPE
            SYNTAX Integer32 (1..900)
            MAX-ACCESS read-write
            STATUS current
            DESCRIPTION
                "Transmitted Levels 1 Threshold Second (TLTS1) 15 minute.
                Alarm Reset threshold in number of seconds that
                RF Output Power are allowed above the
                TLTS1 Alarm Threshold for Maximum RF Output Power
                for entire current 15 minute interval.
                Always less or equal to alarm Set, xfExtRFPMSetThreshold15mTLTS1."
            DEFVAL {20}
            ::= { xfRLExtRFPMConfigEntry 11 }

        xfExtRFPMSetThreshold15mTLTM OBJECT-TYPE
            SYNTAX Integer32 (1..145)
            MAX-ACCESS read-write
            STATUS current
            DESCRIPTION
                "Transmitted Level Tide Mark (TLTM) 15 minute.
                Alarm Set threshold for maximum allowed
                max / min difference of RF Output Power
                in current 15 minute interval.
                RF output level = value dB.
                Domain: [1 ... 145 dB]
                Always greater or equal to alarm Reset, xfExtRFPMResetThreshold15mTLTM."
            DEFVAL {145}
            ::= { xfRLExtRFPMConfigEntry 12 }

        xfExtRFPMResetThreshold15mTLTM OBJECT-TYPE
            SYNTAX Integer32 (1..145)
            MAX-ACCESS read-write
            STATUS current
            DESCRIPTION
                "Transmitted Level Tide Mark (TLTM) 15 minute.
                Alarm Reset threshold for maximum allowed
                max / min difference of RF Output Power
                for entire current 15 minute interval.
                RF output level = value dB.
                Domain: [1 ... 145 dB]
                Always less or equal to alarm Set, xfExtRFPMSetThreshold15mTLTM."
            DEFVAL {144}
            ::= { xfRLExtRFPMConfigEntry 13 }

        xfExtRFPMSetThreshold24hRLTS1 OBJECT-TYPE
            SYNTAX Integer32 (1..86400)
            MAX-ACCESS read-write
            STATUS current
            DESCRIPTION
                "Received Level 1 Threshold Second (RLTS1) 24 hour.
                Alarm Set / Reset threshold in number of seconds that
                RF Input Power are allowed below the
                RLTS1 Alarm Threshold for Minimum RF Input Power
                in current 24 hour interval."
            DEFVAL {20}
            ::= { xfRLExtRFPMConfigEntry 14 }

        xfExtRFPMSetThreshold24hRLTS2 OBJECT-TYPE
            SYNTAX Integer32 (1..86400)
            MAX-ACCESS read-write
            STATUS current
            DESCRIPTION
                "Received Level 2 Threshold Second (RLTS2) 24 hour.
                Alarm Set / Reset threshold in number of seconds that
                RF Input Power are allowed below the
                RLTS2 Alarm Threshold for Minimum RF Input Power
                in current 24 hour interval."
            DEFVAL {1500}
            ::= { xfRLExtRFPMConfigEntry 15 }

        xfExtRFPMSetThreshold24hRLTM OBJECT-TYPE
            SYNTAX Integer32 (10..800)
            MAX-ACCESS read-write
            STATUS current
            DESCRIPTION
                "Receive Level Tide Mark (RLTM) 24 hour.
                Alarm Set / Reset threshold for maximum allowed
                max / min difference of RF Input Power
                in current 24 hour interval.
                RF input level = value/10 dB.
                Domain: [1.0 ... 80.0 dB]"
            DEFVAL {800}
            ::= { xfRLExtRFPMConfigEntry 16 }

        xfExtRFPMSetThreshold24hTLTS1 OBJECT-TYPE
            SYNTAX Integer32 (1..86400)
            MAX-ACCESS read-write
            STATUS current
            DESCRIPTION
                "Transmitted Levels 1 Threshold Second (TLTS1) 24 hour.
                Alarm Set / Reset threshold in number of seconds that
                RF Output Power are allowed above the
                TLTS1 Alarm Threshold for Maximum RF Output Power
                in current 24 hour interval."
            DEFVAL {1500}
            ::= { xfRLExtRFPMConfigEntry 17 }

        xfExtRFPMSetThreshold24hTLTM OBJECT-TYPE
            SYNTAX Integer32 (1..145)
            MAX-ACCESS read-write
            STATUS current
            DESCRIPTION
                "Transmitted Level Tide Mark (TLTM) 24 hour.
                Alarm Set / Reset threshold for maximum allowed
                max / min difference of RF Output Power
                in current 24 hour interval.
                RF output level = value dB.
                Domain: [1 ... 145 dB]"
            DEFVAL {145}
            ::= { xfRLExtRFPMConfigEntry 18 }

        xfExtRFPMStatus OBJECT-TYPE
            SYNTAX BITS
            {
                rlts1Counter15m0(0),
                rlts1Counter15m1(1),
                rlts1Counter15m2(2),

                rlts2Counter15m0(3),
                rlts2Counter15m1(4),
                rlts2Counter15m2(5),

                rltmCounter15m0(6),
                rltmCounter15m1(7),
                rltmCounter15m2(8),

                tlts1Counter15m0(9),
                tlts1Counter15m1(10),
                tlts1Counter15m2(11),

                tltmCounter15m0(12),
                tltmCounter15m1(13),
                tltmCounter15m2(14),

                rlts1Counter24h0(15),
                rlts1Counter24h1(16),
                rlts1Counter24h2(17),

                rlts2Counter24h0(18),
                rlts2Counter24h1(19),
                rlts2Counter24h2(20),

                rltmCounter24h0(21),
                rltmCounter24h1(22),
                rltmCounter24h2(23),

                tlts1Counter24h0(24),
                tlts1Counter24h1(25),
                tlts1Counter24h2(26),

                tltmCounter24h0(27),
                tltmCounter24h1(28),
                tltmCounter24h2(29)
            }
            MAX-ACCESS read-only
            STATUS current
            DESCRIPTION
                "Threshold alarm status"
            ::= { xfRLExtRFPMConfigEntry 19 }

        xfExtRFPMView OBJECT-TYPE
            SYNTAX INTEGER
            {
                extPmEnable(1),
                extPmDisable(2)
            }
            MAX-ACCESS read-write
            STATUS current
            DESCRIPTION
                "
                Enable/disable visibility of PM tables.
                Default value: extPmEnable(1)
                Near end access: read-write
                Far end access: No access
                "
            ::= { xfRLExtRFPMConfigEntry 20 }

--
-- xfRLExtRFPMCurrent24hTable
--

        xfRLExtRFPMCurrent24hTable OBJECT-TYPE
            SYNTAX SEQUENCE OF XfRLExtRFPMCurrent24hEntry
            MAX-ACCESS not-accessible
            STATUS current
            DESCRIPTION
                "Current 24h Extended RF PM table.
                Its index is RF IF ifIndex"
            ::= { xfRadioLinkPtpTerminalObjects 28 }

        xfRLExtRFPMCurrent24hEntry OBJECT-TYPE
            SYNTAX XfRLExtRFPMCurrent24hEntry
            MAX-ACCESS not-accessible
            STATUS current
            DESCRIPTION
                "Entry in the xfRLExtRFPMCurrent24hTable."
            INDEX { ifIndex } --RF IF ifIndex
            ::= { xfRLExtRFPMCurrent24hTable 1 }

        XfRLExtRFPMCurrent24hEntry ::=
            SEQUENCE
            {
                xfExtRFPMCurrent24hElapsedTime  Counter32,
                xfExtRFPMCurrent24hRLTS1        Integer32,
                xfExtRFPMCurrent24hRLTS2        Integer32,
                xfExtRFPMCurrent24hRLMin        Integer32,
                xfExtRFPMCurrent24hRLMax        Integer32,
                xfExtRFPMCurrent24hTLTS1        Integer32,
                xfExtRFPMCurrent24hTLMin        Integer32,
                xfExtRFPMCurrent24hTLMax        Integer32
            }
--
-- The xfRLExtRFPMCurrent24hTable MOs
--

        xfExtRFPMCurrent24hElapsedTime OBJECT-TYPE
            SYNTAX Counter32
            MAX-ACCESS read-only
            STATUS current
            DESCRIPTION
                "The number of seconds that have elapsed since the
                beginning of the current error-measurement period.

                If the current interval exceeds the maximum value,
                the agent will return the maximum value.
                "
            ::= { xfRLExtRFPMCurrent24hEntry 1 }

        xfExtRFPMCurrent24hRLTS1 OBJECT-TYPE
            SYNTAX Integer32 (-1 | 0..86400)
            MAX-ACCESS read-only
            STATUS current
            DESCRIPTION
                "Received Level 1 Threshold Second (RLTS1) 24 hour.
                Number of seconds that the RF Input Power was below the RLTS1
                in the current 24 hour interval.
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent24hEntry 2 }

        xfExtRFPMCurrent24hRLTS2 OBJECT-TYPE
            SYNTAX Integer32 (-1 | 0..86400)
            MAX-ACCESS read-only
            STATUS current
            DESCRIPTION
                "Received Level 2 Threshold Second (RLTS2) 24 hour.
                Number of seconds that the RF Input Power was below the RLTS2
                in the current 24 hour interval.
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent24hEntry 3 }

        xfExtRFPMCurrent24hRLMin OBJECT-TYPE
            SYNTAX Integer32 (-999..-200|0)
            MAX-ACCESS read-only
            STATUS current
            DESCRIPTION
                "Indicate Min RF Input level in current 24 hour interval.
                RF input level = value/10 dBm.
                Domain: [-99.9 ... -20.0 dBm]
                0 (zero) indicates invalid value.
                 The instances are reset by:
                  * xfTermPerfReset in xfRLPtpTerminalPerformanceTable for MMU2 X / MMU3 X
                  * xfPMPerfReset in xfRLPMContinuousCounterTable for MMU4 / MMU1002"
            ::= { xfRLExtRFPMCurrent24hEntry 4 }

        xfExtRFPMCurrent24hRLMax OBJECT-TYPE
            SYNTAX Integer32 (-999..-200|0)
            MAX-ACCESS read-only
            STATUS current
            DESCRIPTION
                "Indicate Max RF Input level in current 24 hour interval.
                RF input level = value/10 dBm.
                Domain: [-99.9 ... -20.0 dBm]
                0 (zero) indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent24hEntry 5 }

        xfExtRFPMCurrent24hTLTS1 OBJECT-TYPE
            SYNTAX Integer32 (-1 | 0..86400)
            MAX-ACCESS read-only
            STATUS current
            DESCRIPTION
                "Transmitted Level 1 Threshold Second (TLTS1) 24 hour.
                Number of seconds that the RF Output Power was above the TLTS1
                in the current 24 hour interval
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent24hEntry 6 }

        xfExtRFPMCurrent24hTLMin OBJECT-TYPE
            SYNTAX Integer32 (-100..45|255)
            MAX-ACCESS read-only
            STATUS current
            DESCRIPTION
                "Indicate Min RF Output level in current 24 hour interval.
                RF output level = value dBm.
                Domain: [-100 ... 45 dBm]
                255 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent24hEntry 7 }

        xfExtRFPMCurrent24hTLMax OBJECT-TYPE
            SYNTAX Integer32 (-100..45|255)
            MAX-ACCESS read-only
            STATUS current
            DESCRIPTION
                "Indicate Max RF Output level in current 24 hour interval.
                RF output level = value dBm.
                Domain: [-100 ... 45 dBm]
                255 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent24hEntry 8 }

--
-- xfRLExtRFPMInterval24hTable
--

        xfRLExtRFPMInterval24hTable OBJECT-TYPE
            SYNTAX SEQUENCE OF XfRLExtRFPMInterval24hEntry
            MAX-ACCESS not-accessible
            STATUS current
            DESCRIPTION
                "Interval 24h Extended RF PM table.
                Its index is RF IF ifIndex"
            ::= { xfRadioLinkPtpTerminalObjects 29 }

        xfRLExtRFPMInterval24hEntry OBJECT-TYPE
            SYNTAX XfRLExtRFPMInterval24hEntry
            MAX-ACCESS not-accessible
            STATUS current
            DESCRIPTION
                "Entry in the xfRLExtRFPMInterval24hTable."
            INDEX { ifIndex } -- RF IF ifIndex
            ::= { xfRLExtRFPMInterval24hTable 1 }

        XfRLExtRFPMInterval24hEntry ::=
            SEQUENCE
            {
                xfExtRFPMInterval24hRLTS1       Integer32,
                xfExtRFPMInterval24hRLTS2       Integer32,
                xfExtRFPMInterval24hRLMin       Integer32,
                xfExtRFPMInterval24hRLMax       Integer32,
                xfExtRFPMInterval24hTLTS1       Integer32,
                xfExtRFPMInterval24hTLMin       Integer32,
                xfExtRFPMInterval24hTLMax       Integer32,
                xfExtRFPMInterval24hValidData   TruthValue
            }

--
-- The xfRLExtRFPMInterval24hTable MOs
--
        xfExtRFPMInterval24hRLTS1 OBJECT-TYPE
            SYNTAX Integer32 (-1 | 0..86400)
            MAX-ACCESS read-only
            STATUS current
            DESCRIPTION
                "Received Level 1 Threshold Second (RLTS1) 24 hour.
                Number of seconds that the RF Input Power was below the RLTS1
                in the previous 24 hour interval.
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval24hEntry 1 }

        xfExtRFPMInterval24hRLTS2 OBJECT-TYPE
            SYNTAX Integer32 (-1 | 0..86400)
            MAX-ACCESS read-only
            STATUS current
            DESCRIPTION
                "Received Level 2 Threshold Second (RLTS2) 24 hour.
                Number of seconds that the RF Input Power was below the RLTS2
                in the previous 24 hour interval.
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval24hEntry 2 }

        xfExtRFPMInterval24hRLMin OBJECT-TYPE
            SYNTAX Integer32 (-999..-200|0)
            MAX-ACCESS read-only
            STATUS current
            DESCRIPTION
                "Indicate Min RF Input level in previous 24 hour interval.
                RF input level = value/10 dBm.
                Domain: [-99.9 ... -20.0 dBm]
                0 (zero) indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval24hEntry 3 }

        xfExtRFPMInterval24hRLMax OBJECT-TYPE
            SYNTAX Integer32 (-999..-200|0)
            MAX-ACCESS read-only
            STATUS current
            DESCRIPTION
                "Indicate Max RF Input level in previous 24 hour interval.
                RF input level = value/10 dBm.
                Domain: [-99.9 ... -20.0 dBm]
                0 (zero) indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval24hEntry 4 }

        xfExtRFPMInterval24hTLTS1 OBJECT-TYPE
            SYNTAX Integer32 (-1 | 0..86400)
            MAX-ACCESS read-only
            STATUS current
            DESCRIPTION
                "Transmitted Level 1 Threshold Second (TLTS1) 24 hour.
                Number of seconds that the RF Output Power was above the TLTS1
                in the previous 24 hour interval
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval24hEntry 5 }

        xfExtRFPMInterval24hTLMin OBJECT-TYPE
            SYNTAX Integer32 (-100..45|255)
            MAX-ACCESS read-only
            STATUS current
            DESCRIPTION
                "Indicate Min RF Output level in previous 24 hour interval.
                RF output level = value dBm.
                Domain: [-100 ... 45 dBm]
                255 indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval24hEntry 6 }

        xfExtRFPMInterval24hTLMax OBJECT-TYPE
            SYNTAX Integer32 (-100..45|255)
            MAX-ACCESS read-only
            STATUS current
            DESCRIPTION
                "Indicate Max RF Output level in previous 24 hour interval.
                RF output level = value dBm.
                Domain: [-100 ... 45 dBm]
                255 indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval24hEntry 7 }

        xfExtRFPMInterval24hValidData OBJECT-TYPE
            SYNTAX TruthValue
            MAX-ACCESS read-only
            STATUS current
            DESCRIPTION
                "This variable indicates whether the data
                for this interval is valid."
            ::= { xfRLExtRFPMInterval24hEntry 8 }

--
-- xfRLExtRFPMCurrent15mTable
--

        xfRLExtRFPMCurrent15mTable OBJECT-TYPE
            SYNTAX SEQUENCE OF XfRLExtRFPMCurrent15mEntry
            MAX-ACCESS not-accessible
            STATUS current
            DESCRIPTION
                "Current 15m Extended RF PM table.
                Its index is RF IF ifIndex"
            ::= { xfRadioLinkPtpTerminalObjects 30 }

        xfRLExtRFPMCurrent15mEntry OBJECT-TYPE
            SYNTAX XfRLExtRFPMCurrent15mEntry
            MAX-ACCESS not-accessible
            STATUS current
            DESCRIPTION
                "Entry in the table."
            INDEX { ifIndex } -- RF IF ifIndex
            ::= { xfRLExtRFPMCurrent15mTable 1 }

        XfRLExtRFPMCurrent15mEntry ::=
            SEQUENCE
            {
                xfExtRFPMCurrent15mElapsedTime  Counter32,
                xfExtRFPMCurrent15mRLTS1        Integer32,
                xfExtRFPMCurrent15mRLTS2        Integer32,
                xfExtRFPMCurrent15mRLMin        Integer32,
                xfExtRFPMCurrent15mRLMax        Integer32,
                xfExtRFPMCurrent15mTLTS1        Integer32,
                xfExtRFPMCurrent15mTLMin        Integer32,
                xfExtRFPMCurrent15mTLMax        Integer32
            }

--
-- The xfRLExtRFPMCurrent15mTable MOs
--

        xfExtRFPMCurrent15mElapsedTime OBJECT-TYPE
            SYNTAX Counter32
            MAX-ACCESS read-only
            STATUS current
            DESCRIPTION
                "The number of seconds that have elapsed since the beginning of
                the current error-measurement period.
                "
            ::= { xfRLExtRFPMCurrent15mEntry 1 }

        xfExtRFPMCurrent15mRLTS1 OBJECT-TYPE
            SYNTAX Integer32 (-1 | 0..900)
            MAX-ACCESS read-only
            STATUS current
            DESCRIPTION
                "Received Level 1 Threshold Second (RLTS1) 15 minute
                Number of seconds that the RF Input Power was below the RLTS1
                in the current 15 minute interval.
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent15mEntry 2 }

        xfExtRFPMCurrent15mRLTS2 OBJECT-TYPE
            SYNTAX Integer32 (-1 | 0..900)
            MAX-ACCESS read-only
            STATUS current
            DESCRIPTION
                "Received Level 2 Threshold Second (RLTS2) 15 minute
                Number of seconds that the RF Input Power was below the RLTS2
                in the current 15 minute interval.
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent15mEntry 3 }

        xfExtRFPMCurrent15mRLMin OBJECT-TYPE
            SYNTAX Integer32 (-999..-200|0)
            MAX-ACCESS read-only
            STATUS current
            DESCRIPTION
                "Indicate Min RF Input level in current 15 minute interval.
                RF input level = value/10 dBm.
                Domain: [-99.9 ... -20.0 dBm]
                0 (zero) indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent15mEntry 4 }

         xfExtRFPMCurrent15mRLMax OBJECT-TYPE
            SYNTAX Integer32 (-999..-200|0)
            MAX-ACCESS read-only
            STATUS current
            DESCRIPTION
                "Indicate Max RF Input level in current 15 minute interval.
                RF input level = value/10 dBm.
                Domain: [-99.9 ... -20.0 dBm]
                0 (zero) indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent15mEntry 5 }

        xfExtRFPMCurrent15mTLTS1 OBJECT-TYPE
            SYNTAX Integer32 (-1 | 0..900)
            MAX-ACCESS read-only
            STATUS current
            DESCRIPTION
                "Transmitted Level 1 Threshold Second (TLTS1) 15 minute
                Number of seconds that the RF Output Power was above the TLTS1
                in the current 15 minute interval
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent15mEntry 6 }

        xfExtRFPMCurrent15mTLMin OBJECT-TYPE
            SYNTAX Integer32 (-100..45|255)
            MAX-ACCESS read-only
            STATUS current
            DESCRIPTION
                "Indicate Min RF Output level in current 15 minute interval.
                RF output level = value dBm.
                Domain: [-100 ... 45 dBm]
                255 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent15mEntry 7 }

        xfExtRFPMCurrent15mTLMax OBJECT-TYPE
            SYNTAX Integer32 (-100..45|255)
            MAX-ACCESS read-only
            STATUS current
            DESCRIPTION
                "Indicate Max RF Output level in current 15 minute interval.
                RF output level = value dBm.
                Domain: [-100 ... 45 dBm]
                255 indicates invalid value.
                The instances are reset by:
                  * xfTermPerfReset in xfRLPtpTerminalPerformanceTable for MMU2 X / MMU3 X
                  * xfPMPerfReset in xfRLPMContinuousCounterTable for MMU4 / MMU1002"
            ::= { xfRLExtRFPMCurrent15mEntry 8 }

--
-- xfRLExtRFPMInterval15mTable
--

        xfRLExtRFPMInterval15mTable OBJECT-TYPE
            SYNTAX SEQUENCE OF XfRLExtRFPMInterval15mEntry
            MAX-ACCESS not-accessible
            STATUS current
            DESCRIPTION
                "Interval 15m Extended RF PM table.
                Its index is RF IF ifIndex"
            ::= { xfRadioLinkPtpTerminalObjects 31 }

        xfRLExtRFPMInterval15mEntry OBJECT-TYPE
            SYNTAX XfRLExtRFPMInterval15mEntry
            MAX-ACCESS not-accessible
            STATUS current
            DESCRIPTION
                "Entry in the table."
            INDEX { ifIndex, xfExtRFPMInterval15mIntervalNumber } -- RF IF ifIndex
            ::= { xfRLExtRFPMInterval15mTable 1 }

        XfRLExtRFPMInterval15mEntry ::=
            SEQUENCE
            {
                xfExtRFPMInterval15mIntervalNumber  Integer32,
                xfExtRFPMInterval15mRLTS1           Integer32,
                xfExtRFPMInterval15mRLTS2           Integer32,
                xfExtRFPMInterval15mRLMin           Integer32,
                xfExtRFPMInterval15mRLMax           Integer32,
                xfExtRFPMInterval15mTLTS1           Integer32,
                xfExtRFPMInterval15mTLMin           Integer32,
                xfExtRFPMInterval15mTLMax           Integer32,
                xfExtRFPMInterval15mValidData       TruthValue
            }

--
-- The xfRLExtRFPMInterval15mTable MOs
--
        xfExtRFPMInterval15mIntervalNumber OBJECT-TYPE
            SYNTAX Integer32 (1..96)
            MAX-ACCESS read-only
            STATUS current
            DESCRIPTION
                "A number between 1 and 96, which identifies the interval for which
                the set of statistics is available. The interval identified by 1
                is the most recently completed 15 minute interval, and the interval
                identified by N is the interval immediately preceding the one
                identified by N-1."
            ::= { xfRLExtRFPMInterval15mEntry 1 }

        xfExtRFPMInterval15mRLTS1 OBJECT-TYPE
            SYNTAX Integer32 (-1 | 0..900)
            MAX-ACCESS read-only
            STATUS current
            DESCRIPTION
                "Received Level 1 Threshold Second (RLTS1) 15 minute
                Number of seconds that the RF Input Power was below the RLTS1
                in the previous 15 minute interval.
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval15mEntry 2 }

        xfExtRFPMInterval15mRLTS2 OBJECT-TYPE
            SYNTAX Integer32 (-1 | 0..900)
            MAX-ACCESS read-only
            STATUS current
            DESCRIPTION
                "Received Level 2 Threshold Second (RLTS2) 15 minute
                Number of seconds that the RF Input Power was below the RLTS2
                in the previous 15 minute interval.
                -1 indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval15mEntry 3 }

        xfExtRFPMInterval15mRLMin OBJECT-TYPE
            SYNTAX Integer32 (-999..-200|0)
            MAX-ACCESS read-only
            STATUS current
            DESCRIPTION
                "Indicate Min RF Input level in previous 15 minute interval.
                RF input level = value/10 dBm.
                Domain: [-99.9 ... -20.0 dBm]
                0 (zero) indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval15mEntry 4 }

         xfExtRFPMInterval15mRLMax OBJECT-TYPE
            SYNTAX Integer32 (-999..-200|0)
            MAX-ACCESS read-only
            STATUS current
            DESCRIPTION
                "Indicate Max RF Input level in previous 15 minute interval.
                RF input level = value/10 dBm.
                Domain: [-99.9 ... -20.0 dBm]
                0 (zero) indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval15mEntry 5 }

        xfExtRFPMInterval15mTLTS1 OBJECT-TYPE
            SYNTAX Integer32 (-1 | 0..900)
            MAX-ACCESS read-only
            STATUS current
            DESCRIPTION
                "Transmitted Level 1 Threshold Second (TLTS1) 15 minute
                Number of seconds that the RF Output Power was above the TLTS1
                in the previous 15 minute interval
                -1 indicates invalid value.
                The instances are reset by:
                  * xfTermPerfReset in xfRLPtpTerminalPerformanceTable for MMU2 X / MMU3 X
                  * xfPMPerfReset in xfRLPMContinuousCounterTable for MMU4 / MMU1002"
           ::= { xfRLExtRFPMInterval15mEntry 6 }

        xfExtRFPMInterval15mTLMin OBJECT-TYPE
            SYNTAX Integer32 (-100..45|255)
            MAX-ACCESS read-only
            STATUS current
            DESCRIPTION
                "Indicate Min RF Output level in previous 15 minute interval.
                RF output level = value dBm.
                Domain: [-100 ... 45 dBm]
                255 indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval15mEntry 7 }

        xfExtRFPMInterval15mTLMax OBJECT-TYPE
            SYNTAX Integer32 (-100..45|255)
            MAX-ACCESS read-only
            STATUS current
            DESCRIPTION
                "Indicate Max RF Output level in previous 15 minute interval.
                RF output level = value dBm.
                Domain: [-100 ... 45 dBm]
                255 indicates invalid value.
                The instances are reset by:
                  * xfTermPerfReset in xfRLPtpTerminalPerformanceTable for MMU2 X / MMU3 X
                  * xfPMPerfReset in xfRLPMContinuousCounterTable for MMU4 / MMU1002"
            ::= { xfRLExtRFPMInterval15mEntry 8 }

        xfExtRFPMInterval15mValidData OBJECT-TYPE
            SYNTAX TruthValue
            MAX-ACCESS read-only
            STATUS current
            DESCRIPTION
                "This variable indicates if the data for this interval is valid."
            ::= { xfRLExtRFPMInterval15mEntry 9 }

--
-- xfRLExtRAUPMCurrent24hTable
--

        xfRLExtRAUPMCurrent24hTable OBJECT-TYPE
            SYNTAX SEQUENCE OF XfRLExtRAUPMCurrent24hEntry
            MAX-ACCESS not-accessible
            STATUS current
            DESCRIPTION
                "Current 24h Extended RAU PM table.
                Its index is RAU IF ifIndex"
            ::= { xfRadioLinkPtpTerminalObjects 32 }

        xfRLExtRAUPMCurrent24hEntry OBJECT-TYPE
            SYNTAX XfRLExtRAUPMCurrent24hEntry
            MAX-ACCESS not-accessible
            STATUS current
            DESCRIPTION
                "Entry in the xfRLExtRAUPMCurrent24hTable."
            INDEX { ifIndex } --RAU IF ifIndex
            ::= { xfRLExtRAUPMCurrent24hTable 1 }

        XfRLExtRAUPMCurrent24hEntry ::=
            SEQUENCE {
                xfExtRAUPMCurrent24hElapsedTime     Counter32,
                xfExtRAUPMCurrent24hMSEMin          Integer32,
                xfExtRAUPMCurrent24hMSEMax          Integer32,
                xfExtRAUPMCurrent24hXPIMin          Integer32,
                xfExtRAUPMCurrent24hXPIMax          Integer32
            }

--
-- The xfRLExtRAUPMCurrent24hTable MOs
--

        xfExtRAUPMCurrent24hElapsedTime OBJECT-TYPE
            SYNTAX Counter32
            MAX-ACCESS read-only
            STATUS current
            DESCRIPTION
                "The number of seconds that have elapsed since the
                beginning of the current error-measurement period.

                If the current interval exceeds the maximum value,
                the agent will return the maximum value.
                "
            ::= { xfRLExtRAUPMCurrent24hEntry 1 }

        xfExtRAUPMCurrent24hMSEMin OBJECT-TYPE
            SYNTAX Integer32 (-1000..1000|2000)
            MAX-ACCESS read-only
            STATUS current
            DESCRIPTION
                "Indicate Min MSE level
                in current 24 hour interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMCurrent24hEntry 2 }

        xfExtRAUPMCurrent24hMSEMax OBJECT-TYPE
            SYNTAX Integer32 (-1000..1000|2000)
            MAX-ACCESS read-only
            STATUS current
            DESCRIPTION
                "Indicate Max MSE level
                in current 24 hour interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMCurrent24hEntry 3 }

        xfExtRAUPMCurrent24hXPIMin OBJECT-TYPE
            SYNTAX Integer32 (-1000..1000|2000)
            MAX-ACCESS read-only
            STATUS current
            DESCRIPTION
                "Indicate Min Cross-Polar Interference (XPI) level
                in current 24 hour interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMCurrent24hEntry 4 }

        xfExtRAUPMCurrent24hXPIMax OBJECT-TYPE
            SYNTAX Integer32 (-1000..1000|2000)
            MAX-ACCESS read-only
            STATUS current
            DESCRIPTION
                "Indicate Max Cross-Polar Interference (XPI) level
                in current 24 hour interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMCurrent24hEntry 5 }

--
-- xfRLExtRAUPMInterval24hTable
--

        xfRLExtRAUPMInterval24hTable OBJECT-TYPE
            SYNTAX SEQUENCE OF XfRLExtRAUPMInterval24hEntry
            MAX-ACCESS not-accessible
            STATUS current
            DESCRIPTION
                "Interval 24h Extended RAU PM table.
                Its index is RAU IF ifIndex"
            ::= { xfRadioLinkPtpTerminalObjects 33 }

        xfRLExtRAUPMInterval24hEntry OBJECT-TYPE
            SYNTAX XfRLExtRAUPMInterval24hEntry
            MAX-ACCESS not-accessible
            STATUS current
            DESCRIPTION
                "Entry in the xfRLExtRAUPMInterval24hTable."
            INDEX { ifIndex }  -- RAU IF ifIndex
            ::= { xfRLExtRAUPMInterval24hTable 1 }

        XfRLExtRAUPMInterval24hEntry ::=
            SEQUENCE {
                xfExtRAUPMInterval24hMSEMin         Integer32,
                xfExtRAUPMInterval24hMSEMax         Integer32,
                xfExtRAUPMInterval24hXPIMin         Integer32,
                xfExtRAUPMInterval24hXPIMax         Integer32,
                xfExtRAUPMInterval24hValidData      TruthValue
            }

--
-- The xfRLExtRAUPMInterval24hTable MOs
--

        xfExtRAUPMInterval24hMSEMin OBJECT-TYPE
            SYNTAX Integer32 (-1000..1000|2000)
            MAX-ACCESS read-only
            STATUS current
            DESCRIPTION
                "Indicate Min MSE level
                in previous 24 hour interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMInterval24hEntry 1 }

        xfExtRAUPMInterval24hMSEMax OBJECT-TYPE
            SYNTAX Integer32 (-1000..1000|2000)
            MAX-ACCESS read-only
            STATUS current
            DESCRIPTION
                "Indicate Max MSE level
                in previous 24 hour interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMInterval24hEntry 2 }

        xfExtRAUPMInterval24hXPIMin OBJECT-TYPE
            SYNTAX Integer32 (-1000..1000|2000)
            MAX-ACCESS read-only
            STATUS current
            DESCRIPTION
                "Indicate Min Cross-Polar Interference (XPI) level
                in previous 24 hour interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMInterval24hEntry 3 }

        xfExtRAUPMInterval24hXPIMax OBJECT-TYPE
            SYNTAX Integer32 (-1000..1000|2000)
            MAX-ACCESS read-only
            STATUS current
            DESCRIPTION
                "Indicate Max Cross-Polar Interference (XPI) level
                in previous 24 hour interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMInterval24hEntry 4 }

        xfExtRAUPMInterval24hValidData OBJECT-TYPE
            SYNTAX TruthValue
            MAX-ACCESS read-only
            STATUS current
            DESCRIPTION
                "This variable indicates whether the data
                for this interval is valid."
            ::= { xfRLExtRAUPMInterval24hEntry 5 }

--
-- xfRLExtRAUPMCurrent15mTable --
--

        xfRLExtRAUPMCurrent15mTable OBJECT-TYPE
            SYNTAX SEQUENCE OF XfRLExtRAUPMCurrent15mEntry
            MAX-ACCESS not-accessible
            STATUS current
            DESCRIPTION
                "Current 15m Extended RAU PM table.
                Its index is RF IF ifIndex"
            ::= { xfRadioLinkPtpTerminalObjects 34 }

        xfRLExtRAUPMCurrent15mEntry OBJECT-TYPE
            SYNTAX XfRLExtRAUPMCurrent15mEntry
            MAX-ACCESS not-accessible
            STATUS current
            DESCRIPTION
                "Entry in the xfRLExtRAUPMCurrent15mTable."
            INDEX { ifIndex } --RAU IF ifIndex
            ::= { xfRLExtRAUPMCurrent15mTable 1 }

        XfRLExtRAUPMCurrent15mEntry ::=
            SEQUENCE {
                xfExtRAUPMCurrent15mElapsedTime     Counter32,
                xfExtRAUPMCurrent15mMSEMin          Integer32,
                xfExtRAUPMCurrent15mMSEMax          Integer32,
                xfExtRAUPMCurrent15mXPIMin          Integer32,
                xfExtRAUPMCurrent15mXPIMax          Integer32
            }

--
-- The xfRLExtRAUPMInterval15mTable MOs
--

        xfExtRAUPMCurrent15mElapsedTime OBJECT-TYPE
            SYNTAX Counter32
            MAX-ACCESS read-only
            STATUS current
            DESCRIPTION
                "The number of seconds that have elapsed since the
                beginning of the current error-measurement period.

                If the current interval exceeds the maximum value,
                the agent will return the maximum value.
                "
            ::= { xfRLExtRAUPMCurrent15mEntry 1 }

        xfExtRAUPMCurrent15mMSEMin OBJECT-TYPE
            SYNTAX Integer32 (-1000..1000|2000)
            MAX-ACCESS read-only
            STATUS current
            DESCRIPTION
                "Indicate Min MSE level
                in current 15 mimute interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMCurrent15mEntry 2 }

        xfExtRAUPMCurrent15mMSEMax OBJECT-TYPE
            SYNTAX Integer32 (-1000..1000|2000)
            MAX-ACCESS read-only
            STATUS current
            DESCRIPTION
                "Indicate Max MSE level
                in current 15 mimute interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMCurrent15mEntry 3 }

        xfExtRAUPMCurrent15mXPIMin OBJECT-TYPE
            SYNTAX Integer32 (-1000..1000|2000)
            MAX-ACCESS read-only
            STATUS current
            DESCRIPTION
                "Indicate Min Cross-Polar Interference (XPI) level
                in current 15 mimute interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMCurrent15mEntry 4 }

        xfExtRAUPMCurrent15mXPIMax OBJECT-TYPE
            SYNTAX Integer32 (-1000..1000|2000)
            MAX-ACCESS read-only
            STATUS current
            DESCRIPTION
                "Indicate Max Cross-Polar Interference (XPI) level
                in current 15 mimute interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMCurrent15mEntry 5 }

--
-- xfRLExtRAUPMInterval15mTable
--

        xfRLExtRAUPMInterval15mTable OBJECT-TYPE
            SYNTAX SEQUENCE OF XfRLExtRAUPMInterval15mEntry
            MAX-ACCESS not-accessible
            STATUS current
            DESCRIPTION
                "Interval 15 Extended RAU PM table.
                Its index is RAU IF ifIndex"
            ::= { xfRadioLinkPtpTerminalObjects 35 }

        xfRLExtRAUPMInterval15mEntry OBJECT-TYPE
            SYNTAX XfRLExtRAUPMInterval15mEntry
            MAX-ACCESS not-accessible
            STATUS current
            DESCRIPTION
                "Entry in the xfRLExtRAUPMInterval15mTable."
            INDEX { ifIndex, xfExtRAUPMInterval15mIntervalNumber} -- RAU IF ifIndex
            ::= { xfRLExtRAUPMInterval15mTable 1 }

        XfRLExtRAUPMInterval15mEntry ::=
            SEQUENCE
            {
                xfExtRAUPMInterval15mIntervalNumber     Integer32,
                xfExtRAUPMInterval15mMSEMin             Integer32,
                xfExtRAUPMInterval15mMSEMax             Integer32,
                xfExtRAUPMInterval15mXPIMin             Integer32,
                xfExtRAUPMInterval15mXPIMax             Integer32,
                xfExtRAUPMInterval15mValidData          TruthValue
            }

--
-- The xfRLExtRAUPMInterval15mTable MOs
--

        xfExtRAUPMInterval15mIntervalNumber OBJECT-TYPE
            SYNTAX Integer32 (1..96)
            MAX-ACCESS read-only
            STATUS current
            DESCRIPTION
                "A number between 1 and 96, which identifies the interval for which
                the set of statistics is available. The interval identified by 1
                is the most recently completed 15 minute interval, and the interval
                identified by N is the interval immediately preceding the one
                identified by N-1."
            ::= { xfRLExtRAUPMInterval15mEntry 1 }

        xfExtRAUPMInterval15mMSEMin OBJECT-TYPE
            SYNTAX Integer32 (-1000..1000|2000)
            MAX-ACCESS read-only
            STATUS current
            DESCRIPTION
                "Indicate Min MSE level
                in previous 15 minute interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMInterval15mEntry 2 }

        xfExtRAUPMInterval15mMSEMax OBJECT-TYPE
            SYNTAX Integer32 (-1000..1000|2000)
            MAX-ACCESS read-only
            STATUS current
            DESCRIPTION
                "Indicate Max MSE level
                in previous 15 minute interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMInterval15mEntry 3 }

        xfExtRAUPMInterval15mXPIMin OBJECT-TYPE
            SYNTAX Integer32 (-1000..1000|2000)
            MAX-ACCESS read-only
            STATUS current
            DESCRIPTION
                "Indicate Min Cross-Polar Interference (XPI) level
                in previous 15 minute interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMInterval15mEntry 4 }

        xfExtRAUPMInterval15mXPIMax OBJECT-TYPE
            SYNTAX Integer32 (-1000..1000|2000)
            MAX-ACCESS read-only
            STATUS current
            DESCRIPTION
                "Indicate Max Cross-Polar Interference (XPI) level
                in previous 15 minute interval.
                Input level = value/10 dB.
                Domain: [-100.0 ... 100.0 dB]
                2000 indicates invalid value.
                The instances are reset by:
                  * xfTermPerfReset in xfRLPtpTerminalPerformanceTable for MMU2 X / MMU3 X
                  * xfPMPerfReset in xfRLPMContinuousCounterTable for MMU4 / MMU1002"
            ::= { xfRLExtRAUPMInterval15mEntry 5 }

        xfExtRAUPMInterval15mValidData OBJECT-TYPE
            SYNTAX TruthValue
            MAX-ACCESS read-only
            STATUS current
            DESCRIPTION
                "This variable indicates whether the data
                for this interval is valid."
            ::= { xfRLExtRAUPMInterval15mEntry 6 }

--
-- Conformance
--

  xfRadioLinkPtpTerminalCompliances OBJECT IDENTIFIER
    ::= { xfRadioLinkPtpTerminalConformance 1 }

  xfRadioLinkPtpTerminalGroups OBJECT IDENTIFIER
    ::= { xfRadioLinkPtpTerminalConformance 2 }

  xfRadioLinkPtpTerminalFullCompliance MODULE-COMPLIANCE
    STATUS current
    DESCRIPTION
      "The compliance statement for SNMP entities which implement everything."
    MODULE -- This Module
    MANDATORY-GROUPS { xfRadioLinkPtpTerminalCompleteGroup }
    ::= { xfRadioLinkPtpTerminalCompliances 1 }

  xfRadioLinkPtpTerminalCompleteGroup OBJECT-GROUP
    OBJECTS
    {
      xfTermId,
      xfTermType,
      xfTermProtection,
      xfTermCapacity,
      xfTermCapacityCapability,
      xfTermModulation,
      xfTermModulationCapability,
      xfTermRestore,
      xfTermAlarmSeverity,
      xfTermTrapEnable,
      xfTermAsPort,
      xfTermRemoteIdCheck,
      xfTermRemoteId,
      xfTermPreset,
      xfTermBerAlarmThreshold,
      xfTermFadeNotificationTimer,
      xfTermEquipmentProtectionIndex,
      xfTermSysName,
      xfTermChannelMode,
      xfTermChannelModeCapability,
      xfTermTrafficAndDCN,
      xfTermFrameFormat,
      xfTermFrameFormatCapability,
      xfTermDCNRadioConfiguration,
      xfTermDCNRadioCapability,
      xfTermDCNLineConfiguration,
      xfTermDCNLineCapability,
      xfTermFadeNotificationConfiguration,
      xfTermLineProtection,
      xfTermOutputPowerOperStatus,
      xfTermOutputPowerAdminStatus,
      xfTermAtpcCapability,
      xfTermTimeElapsed,
      xfTermCurrentES,
      xfTermCurrentSES,
      xfTermCurrentBBE,
      xfTermCurrentUAS,
      xfTermCurrentBB,
      xfTermPerfReset,
      xfTermTimeElapsedEnRLBExt,
      xfRLProtectionMode,
      xfRLProtectionRau1,
      xfRLProtectionRau2,
      xfRLActiveTxRadio,
      xfRLSwitchOverReset,
      xfRLSwitchRevertiveTx,
      xfRLProtectionCapability,
      xfRLTxSwitchOverConfiguration,
      xfRLLineProtectionStatus,
      xfRLLineProtectionMode,
      xfRADIORSAlarms,
      xfRADIORSPerformanceAlarms,
      xfPMSetThreshold15mESs,
      xfPMSetThreshold15mSESs,
      xfPMSetThreshold15mBBEs,
      xfPMResetThreshold15mESs,
      xfPMResetThreshold15mSESs,
      xfPMResetThreshold15mBBEs,
      xfPMSetThreshold24hESs,
      xfPMSetThreshold24hSESs,
      xfPMSetThreshold24hBBEs,
      xfPMView,
      xfPMStatus,
      xfPMCurrent24hTimeElapsed,
      xfPMCurrent24hESs,
      xfPMCurrent24hSESs,
      xfPMCurrent24hBBEs,
      xfPMCurrent24hUASs,
      xfPMCurrent24hBBs,
      xfPMInterval24hESs,
      xfPMInterval24hSESs,
      xfPMInterval24hBBEs,
      xfPMInterval24hUASs,
      xfPMInterval24hBBs,
      xfPMInterval24hRLTS1,
      xfPMInterval24hRLTS2,
      xfPMInterval24hRLMin,
      xfPMInterval24hRLMax,
      xfPMInterval24hTLTS1,
      xfPMInterval24hTLMin,
      xfPMInterval24hTLMax,
      xfPMInterval24hMSEMin,
      xfPMInterval24hMSEMax,
      xfPMInterval24hXPIMin,
      xfPMInterval24hXPIMax,
      xfPMInterval24hValidData,
      xfPMCurrent15mElapsedTime,
      xfPMCurrent15mESs,
      xfPMCurrent15mSESs,
      xfPMCurrent15mBBEs,
      xfPMCurrent15mUASs,
      xfPMCurrent15mBBs,
      xfPMInterval15mIntervalNumber,
      xfPMInterval15mESs,
      xfPMInterval15mSESs,
      xfPMInterval15mBBEs,
      xfPMInterval15mUASs,
      xfPMInterval15mBBs,
      xfPMInterval15mRLTS1,
      xfPMInterval15mRLTS2,
      xfPMInterval15mRLMin,
      xfPMInterval15mRLMax,
      xfPMInterval15mTLTS1,
      xfPMInterval15mTLMin,
      xfPMInterval15mTLMax,
      xfPMInterval15mMSEMin,
      xfPMInterval15mMSEMax,
      xfPMInterval15mXPIMin,
      xfPMInterval15mXPIMax,
      xfPMInterval15mValidData,
      xfTermInterfaces,
      xfTermInterfacesCapability,
      xfTermChannelModeOperStatus,
      xfTermXPICRestore,
      xfTermTribCapacityActual,
      xfTermTribCapacityDesired,
      xfTermBitPipeCapacity,
      xfTermRowIndex,
      xfTermCapabilitiesLastChange,
      xfTermActualRowIndex,
      xfTermMaxRowIndex,
      xfTermAdaptiveManualRowIndex,
      xfTermAdaptiveManualMode,
      xfTermSpectrumEfficiencyClass,
      xfTermSpectrumEfficiencyClassCapability,
      xfTermChannelSpacing,
      xfTermChannelModulation,
      xfTermMaxTribCapacity,
      xfTermDCNCapacity,
      xfTermValidRow,
      xfTermMaxCapacity,
      xfTermFrameFormatType,
      xfTermFrameFormatRev,
      xfTermBerAlarmThresholdCapability,
      xfPMAMSetThreshold15m,
      xfPMAMSetThreshold24h,
      xfPMAMResetThreshold15m,
      xfPMAMStatus,
      xfPMAMValidData,
      xfPMAMCurrent24h4QAM,
      xfPMAMCurrent24h8QAM,
      xfPMAMCurrent24h16QAM,
      xfPMAMCurrent24h32QAM,
      xfPMAMCurrent24h64QAM,
      xfPMAMCurrent24h128QAM,
      xfPMAMCurrent24h256QAM,
      xfPMAMCurrent24h512QAM,
      xfPMAMCurrent24h1024QAM,
      xfPMAMInterval24h4QAM,
      xfPMAMInterval24h8QAM,
      xfPMAMInterval24h16QAM,
      xfPMAMInterval24h32QAM,
      xfPMAMInterval24h64QAM,
      xfPMAMInterval24h128QAM,
      xfPMAMInterval24h256QAM,
      xfPMAMInterval24h512QAM,
      xfPMAMInterval24hValidData,
      xfPMAMInterval24h1024QAM,
      xfPMAMCurrent15m4QAM,
      xfPMAMCurrent15m8QAM,
      xfPMAMCurrent15m16QAM,
      xfPMAMCurrent15m32QAM,
      xfPMAMCurrent15m64QAM,
      xfPMAMCurrent15m128QAM,
      xfPMAMCurrent15m256QAM,
      xfPMAMCurrent15m512QAM,
      xfPMAMCurrent15m1024QAM,
      xfPMAMInterval15mIntervalNumber,
      xfPMAMInterval15m4QAM,
      xfPMAMInterval15m8QAM,
      xfPMAMInterval15m16QAM,
      xfPMAMInterval15m32QAM,
      xfPMAMInterval15m64QAM,
      xfPMAMInterval15m128QAM,
      xfPMAMInterval15m256QAM,
      xfPMAMInterval15m512QAM,
      xfPMAMInterval15mValidData,
      xfPMAMInterval15m1024QAM,
      xfPMAMCurrent24h4QAMEnRLB,
      xfPMAMCurrent24h8QAMEnRLB,
      xfPMAMCurrent24h16QAMEnRLB,
      xfPMAMCurrent24h32QAMEnRLB,
      xfPMAMCurrent24h64QAMEnRLB,
      xfPMAMCurrent24h128QAMEnRLB,
      xfPMAMCurrent24h256QAMEnRLB,
      xfPMAMCurrent24h512QAMEnRLB,
      xfPMAMCurrent24h1024QAMEnRLB,
      xfPMAMInterval24h4QAMEnRLB,
      xfPMAMInterval24h8QAMEnRLB,
      xfPMAMInterval24h16QAMEnRLB,
      xfPMAMInterval24h32QAMEnRLB,
      xfPMAMInterval24h64QAMEnRLB,
      xfPMAMInterval24h128QAMEnRLB,
      xfPMAMInterval24h256QAMEnRLB,
      xfPMAMInterval24h512QAMEnRLB,
      xfPMAMInterval24h1024QAMEnRLB,
      xfPMAMCurrent15m4QAMEnRLB,
      xfPMAMCurrent15m8QAMEnRLB,
      xfPMAMCurrent15m16QAMEnRLB,
      xfPMAMCurrent15m32QAMEnRLB,
      xfPMAMCurrent15m64QAMEnRLB,
      xfPMAMCurrent15m128QAMEnRLB,
      xfPMAMCurrent15m256QAMEnRLB,
      xfPMAMCurrent15m512QAMEnRLB,
      xfPMAMCurrent15m1024QAMEnRLB,
      xfPMAMInterval15m4QAMEnRLB,
      xfPMAMInterval15m8QAMEnRLB,
      xfPMAMInterval15m16QAMEnRLB,
      xfPMAMInterval15m32QAMEnRLB,
      xfPMAMInterval15m64QAMEnRLB,
      xfPMAMInterval15m128QAMEnRLB,
      xfPMAMInterval15m256QAMEnRLB,
      xfPMAMInterval15m512QAMEnRLB,
      xfPMAMInterval15m1024QAMEnRLB,
      xfTermIpAddress,
      xfTermProtectionCapability,
      xfTermLineProtectionCapability,
      xfTermTribAllocationActual,
      xfTermTribAllocationDesired,
      xfTermAutoRemoveLoopEnable,
      xfTermCapability,
      xfTermCapacityLicense,
      xfTermCapacityLicenseRange,
      xfTermMaxCapacityRange,
      xfTermMaxTribCapacityRange,
      xfTermFadingRates,
      xfTermFadingRatesCapability,
      xfTermConfiguredBitPipeCapacity,
      xfTermTribCapacityConfigured,
      xfTermPacketMaxCapacity,
      xfTermPacketMinCapacity,
      xfPMSDCGainCurrent15m0005dB,
      xfPMSDCGainCurrent15m0510dB,
      xfPMSDCGainCurrent15m1015dB,
      xfPMSDCGainCurrent15m1520dB,
      xfPMSDCGainCurrent15m2025dB,
      xfPMSDCGainCurrent15m2530dB,
      xfPMSDCGainInterval15mIntervalNumber,
      xfPMSDCGainInterval15m0005dB,
      xfPMSDCGainInterval15m0510dB,
      xfPMSDCGainInterval15m1015dB,
      xfPMSDCGainInterval15m1520dB,
      xfPMSDCGainInterval15m2025dB,
      xfPMSDCGainInterval15m2530dB,
      xfPMSDCGainCurrent24h0005dB,
      xfPMSDCGainCurrent24h0510dB,
      xfPMSDCGainCurrent24h1015dB,
      xfPMSDCGainCurrent24h1520dB,
      xfPMSDCGainCurrent24h2025dB,
      xfPMSDCGainCurrent24h2530dB,
      xfPMSDCGainInterval24h0005dB,
      xfPMSDCGainInterval24h0510dB,
      xfPMSDCGainInterval24h1015dB,
      xfPMSDCGainInterval24h1520dB,
      xfPMSDCGainInterval24h2025dB,
      xfPMSDCGainInterval24h2530dB,
      xfPMSDCGainSetThreshold15m,
      xfPMSDCGainSetThreshold24h,
      xfPMSDCGainResetThreshold15m,
      xfPMSDCGainStatus,
      xfPMRLTS1Threshold,
      xfPMSetThreshold15mRLTS1,
      xfPMResetThreshold15mRLTS1,
      xfPMRLTS2Threshold,
      xfPMSetThreshold15mRLTS2,
      xfPMResetThreshold15mRLTS2,
      xfPMSetThreshold15mRLTM,
      xfPMResetThreshold15mRLTM,
      xfPMTLTS1Threshold,
      xfPMSetThreshold15mTLTS1,
      xfPMResetThreshold15mTLTS1,
      xfPMSetThreshold15mTLTM,
      xfPMResetThreshold15mTLTM,
      xfPMSetThreshold24hRLTS1,
      xfPMSetThreshold24hRLTS2,
      xfPMSetThreshold24hRLTM,
      xfPMSetThreshold24hTLTS1,
      xfPMSetThreshold24hTLTM,
      xfPMCurrent24hRLTS1,
      xfPMCurrent24hRLTS2,
      xfPMCurrent24hRLMin,
      xfPMCurrent24hRLMax,
      xfPMCurrent24hTLTS1,
      xfPMCurrent24hTLMin,
      xfPMCurrent24hTLMax,
      xfPMCurrent24hMSEMin,
      xfPMCurrent24hMSEMax,
      xfPMCurrent24hXPIMin,
      xfPMCurrent24hXPIMax,
      xfPMCurrent15mRLTS1,
      xfPMCurrent15mRLTS2,
      xfPMCurrent15mRLMin,
      xfPMCurrent15mRLMax,
      xfPMCurrent15mTLTS1,
      xfPMCurrent15mTLMin,
      xfPMCurrent15mTLMax,
      xfPMCurrent15mMSEMin,
      xfPMCurrent15mMSEMax,
      xfPMCurrent15mXPIMin,
      xfPMCurrent15mXPIMax,
      xfPMCurrent15mESR,
      xfPMCurrent15mSESR,
      xfPMCurrent15mBBER,
      xfPMCurrent24hESR,
      xfPMCurrent24hSESR,
      xfPMCurrent24hBBER,
 
-- Extended PM
      xfExtRFPMRLTS1Threshold,
      xfExtRFPMSetThreshold15mRLTS1,
      xfExtRFPMResetThreshold15mRLTS1,
      xfExtRFPMRLTS2Threshold,
      xfExtRFPMSetThreshold15mRLTS2,
      xfExtRFPMResetThreshold15mRLTS2,
      xfExtRFPMSetThreshold15mRLTM,
      xfExtRFPMResetThreshold15mRLTM,
      xfExtRFPMTLTS1Threshold,
      xfExtRFPMSetThreshold15mTLTS1,
      xfExtRFPMResetThreshold15mTLTS1,
      xfExtRFPMSetThreshold15mTLTM,
      xfExtRFPMResetThreshold15mTLTM,
      xfExtRFPMSetThreshold24hRLTS1,
      xfExtRFPMSetThreshold24hRLTS2,
      xfExtRFPMSetThreshold24hRLTM,
      xfExtRFPMSetThreshold24hTLTS1,
      xfExtRFPMSetThreshold24hTLTM,
      xfExtRFPMStatus,
      xfExtRFPMView,

      xfExtRFPMCurrent24hElapsedTime,
      xfExtRFPMCurrent24hRLTS1,
      xfExtRFPMCurrent24hRLTS2,
      xfExtRFPMCurrent24hRLMin,
      xfExtRFPMCurrent24hRLMax,
      xfExtRFPMCurrent24hTLTS1,
      xfExtRFPMCurrent24hTLMin,
      xfExtRFPMCurrent24hTLMax,

      xfExtRFPMInterval24hRLTS1,
      xfExtRFPMInterval24hRLTS2,
      xfExtRFPMInterval24hRLMin,
      xfExtRFPMInterval24hRLMax,
      xfExtRFPMInterval24hTLTS1,
      xfExtRFPMInterval24hTLMin,
      xfExtRFPMInterval24hTLMax,
      xfExtRFPMInterval24hValidData,

      xfExtRFPMCurrent15mElapsedTime,
      xfExtRFPMCurrent15mRLTS1,
      xfExtRFPMCurrent15mRLTS2,
      xfExtRFPMCurrent15mRLMin,
      xfExtRFPMCurrent15mRLMax,
      xfExtRFPMCurrent15mTLTS1,
      xfExtRFPMCurrent15mTLMin,
      xfExtRFPMCurrent15mTLMax,

      xfExtRFPMInterval15mIntervalNumber,
      xfExtRFPMInterval15mRLTS1,
      xfExtRFPMInterval15mRLTS2,
      xfExtRFPMInterval15mRLMin,
      xfExtRFPMInterval15mRLMax,
      xfExtRFPMInterval15mTLTS1,
      xfExtRFPMInterval15mTLMin,
      xfExtRFPMInterval15mTLMax,
      xfExtRFPMInterval15mValidData,

      xfExtRAUPMCurrent24hElapsedTime,
      xfExtRAUPMCurrent24hMSEMin,
      xfExtRAUPMCurrent24hMSEMax,
      xfExtRAUPMCurrent24hXPIMin,
      xfExtRAUPMCurrent24hXPIMax,

      xfExtRAUPMInterval24hMSEMin,
      xfExtRAUPMInterval24hMSEMax,
      xfExtRAUPMInterval24hXPIMin,
      xfExtRAUPMInterval24hXPIMax,
      xfExtRAUPMInterval24hValidData,

      xfExtRAUPMCurrent15mElapsedTime,
      xfExtRAUPMCurrent15mMSEMin,
      xfExtRAUPMCurrent15mMSEMax,
      xfExtRAUPMCurrent15mXPIMin,
      xfExtRAUPMCurrent15mXPIMax,

      xfExtRAUPMInterval15mIntervalNumber,
      xfExtRAUPMInterval15mMSEMin,
      xfExtRAUPMInterval15mMSEMax,
      xfExtRAUPMInterval15mXPIMin,
      xfExtRAUPMInterval15mXPIMax,
      xfExtRAUPMInterval15mValidData
    }
    STATUS current
    DESCRIPTION
    "A collection of all current objects in this MIB module."
    ::= { xfRadioLinkPtpTerminalGroups 1 }

    xfRadioLinkPtpTerminalObsoleteGroup OBJECT-GROUP
    OBJECTS
    {
      xfTermSpectrumEfficiencyClassObsolete
    }
    STATUS obsolete
    DESCRIPTION
    "A collection of all obsolete objects in this MIB module."
    ::= { xfRadioLinkPtpTerminalGroups 2 }

END
