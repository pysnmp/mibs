--
-- HUAWEI-SECURITY-STAT-MIB.mib
-- MIB generated by MG-SOFT Visual MIB Builder Version 4.0 Build 341
-- Wednesday, September 12, 2012 at 15:54:13
--

--  HUAWEI-SECURITY-STAT-MIB.mib
-- MIB generated by MG-SOFT Visual MIB Builder Version 4.0 Build 341
-- Friday, August 31, 2012 at 15:11:41
-- 
--  
-- =================================================================
-- Copyright (C) 2017 by  HUAWEI TECHNOLOGIES. All rights reserved
-- 
-- Description:
-- Reference:
-- Version: V1.27
-- History:
-- shaoyu,2009-03-12,<contents>
-- =================================================================

	HUAWEI-SECURITY-STAT-MIB DEFINITIONS ::= BEGIN
 
		IMPORTS
			enterprises			
				FROM RFC1155-SMI			
			OBJECT-GROUP			
				FROM SNMPv2-CONF			
			Integer32, Gauge32, Counter64, OBJECT-TYPE, MODULE-IDENTITY, 
			NOTIFICATION-TYPE			
				FROM SNMPv2-SMI			
			TruthValue			
				FROM SNMPv2-TC;
	
	
		-- 1.3.6.1.4.1.2011.6.122.15.1
		hwSecStatGlobal MODULE-IDENTITY 
			LAST-UPDATED "201708101920Z"		-- Sem 14, 2016 at 19:22 GMT
			ORGANIZATION 
				"Huawei Technologies Co.,Ltd."
			CONTACT-INFO
				"Huawei Industrial Base
                                 Bantian, Longgang
                                 Shenzhen 518129
                                 People's Republic of China
                                 Website: http://www.huawei.com
                                 Email: support@huawei.com"
			DESCRIPTION 
				"
				V1.20
				The HUAWEI-SECSTAT-MIB contains objects to manage the security statistics for firewall product.
				"
			--  Revision history
                                REVISION   "201708101920Z"
                                DESCRIPTION "V1.27 modify the hwSecStatTrapSlot and the hwSecStatPerfTrapCpuThreshold."
                                REVISION   "201707111920Z"
                                DESCRIPTION "V1.26 add the SYNTAX of the hwSecStatFastSessOverThreshold and hwSecStatFastSessBelowThreshold node."
                                REVISION   "201706291920Z"
                                DESCRIPTION "V1.24 modify trap node hwSecStatFragStaSessBelowThreshold ."

                                REVISION   "201705091920Z"
                                DESCRIPTION "V1.23 modify the SYNTAX of the hwSecStatPerfMemUsage and hwSecStatPerfTotalMemUsage node."
                                REVISION   "201704101920Z"
                                DESCRIPTION "V1.22 modify trap node."
                                                                   REVISION   "201702141920Z"
                                DESCRIPTION "V1.22 modify trap node."
			   REVISION   "201611082300Z"
	           DESCRIPTION "V1.21 modify trap node."
			   REVISION   "201611042314Z"
	           DESCRIPTION "V1.20 modify trap node."
				 REVISION   "201611042314Z"
                                 DESCRIPTION "V1.19 modify trap node name."
				 REVISION   "201610222241Z"
                                 DESCRIPTION "V1.18 add forword trap node."
				 REVISION   "201608231641Z"
                                 DESCRIPTION "V1.17 add a hwSecStatDeviceLoggedPackets table node."
				 REVISION   "201608191400Z"
                                 DESCRIPTION "V1.16 modify the hwSecStatSecPolicyRateTable table node."
                                                                                      REVISION   "201603301730Z"
                                 DESCRIPTION "V1.15 add a table node."
                                                                                     REVISION    "201603301730Z"
                                 DESCRIPTION "V1.14, add a table node."
                                                                                      REVISION   "201603171730Z"
                                 DESCRIPTION "V1.13, add a table node."
				 REVISION   "201601151500Z"
                                 DESCRIPTION "V1.12, modify the MAX-ACCESS of the hwSecStatSecHittedVsysName and hwSecStatSecHittedRuleName node ."
				 REVISION   "201512111400Z"
                                 DESCRIPTION "V1.11, modify the syntax type of the hwSecStatFragRate node from octet string to Integer32 ."
				 REVISION    "201010090900Z"
                                 DESCRIPTION "V1.00, completed the first draft."
				 REVISION   "201408300900Z"
                                 DESCRIPTION "V1.01, modifiy the MODULE-IDENTITY."
				 REVISION   "201409280900Z"
                                 DESCRIPTION "V1.02, add a table node."
				 REVISION   "201412160900Z"
                                 DESCRIPTION "V1.03, add a table node."
				 REVISION   "201502110900Z"
                                 DESCRIPTION "V1.04, add a table node."
				 REVISION   "201502250900Z"
                                 DESCRIPTION "V1.05, modify the description of the service-quality statistic node ."
				 REVISION   "201503030900Z"
                                 DESCRIPTION "V1.06, modify the description of the service-quality statistic node ."
				 REVISION   "201503031700Z"
                                 DESCRIPTION "V1.07, modify the MAX-ACCESS of the hwSecStatInterzoneSessTable node ."
				 REVISION   "201505071500Z"
                                 DESCRIPTION "V1.08, modify the type of the service-quality node ."
                 		 REVISION   "201509152000Z"
                                 DESCRIPTION "V1.09, modify the node of the hwSecStatPktRateObjects node ."  
                 		 REVISION   "201510101600Z"
                                 DESCRIPTION "V1.10, modify the node of the hwSecStatPktRateObjects node ."          
                 			     ::= { hwSecStatMibObjects 1 }
              
		
	
	
--
-- Node definitions
--
	
		-- 1.3.6.1.4.1.2011
		huawei OBJECT IDENTIFIER ::= { enterprises 2011 }

		
		-- 1.3.6.1.4.1.2011.6
		huaweiUtility OBJECT IDENTIFIER ::= { huawei 6 }

		
		-- 1.3.6.1.4.1.2011.6.122
		hwSecurity OBJECT IDENTIFIER ::= { huaweiUtility 122 }

		-- 1.3.6.1.4.1.2011.6.122.15
		hwSecStatMibObjects OBJECT IDENTIFIER ::= { hwSecurity 15 }

		-- 1.3.6.1.4.1.2011.6.122.15.1.1
		hwSecStatCfgObjects OBJECT IDENTIFIER ::= { hwSecStatGlobal 1 }

		-- 1.3.6.1.4.1.2011.6.122.15.1.1.1
		hwSecStatGlobalStatEnable OBJECT-TYPE
			SYNTAX TruthValue
			MAX-ACCESS read-write
			STATUS current
			DESCRIPTION
				"The status indicate whether enable the global statistics."
			DEFVAL { true }
			::= { hwSecStatCfgObjects 1 }

		
		-- 1.3.6.1.4.1.2011.6.122.15.1.1.2
		hwSecStatGlobalPktScale OBJECT IDENTIFIER ::= { hwSecStatCfgObjects 2 }

		
		-- 1.3.6.1.4.1.2011.6.122.15.1.1.2.1
		hwSecStatTcpPktScale OBJECT-TYPE
			SYNTAX Integer32 (0..100)
			MAX-ACCESS read-write
			STATUS current
			DESCRIPTION
				"
				The percent of TCP packets.
				
				The hwSecStatTcpPktScale + hwSecStatUdpPktScale + hwSecStatIcmpPktScale
				must less than 100
				"
			::= { hwSecStatGlobalPktScale 1 }

		
		-- 1.3.6.1.4.1.2011.6.122.15.1.1.2.2
		hwSecStatUdpPktScale OBJECT-TYPE
			SYNTAX Integer32 (0..100)
			MAX-ACCESS read-write
			STATUS current
			DESCRIPTION
				"
				The percent of UDP packets.
				
				The hwSecStatTcpPktScale + hwSecStatUdpPktScale + hwSecStatIcmpPktScale
				must less than 100
				"
			::= { hwSecStatGlobalPktScale 2 }

		
		-- 1.3.6.1.4.1.2011.6.122.15.1.1.2.3
		hwSecStatIcmpPktScale OBJECT-TYPE
			SYNTAX Integer32 (0..100)
			MAX-ACCESS read-write
			STATUS current
			DESCRIPTION
				"
				The percent of ICMP packets.
				
				The hwSecStatTcpPktScale + hwSecStatUdpPktScale + hwSecStatIcmpPktScale
				must less than 100
				"
			::= { hwSecStatGlobalPktScale 3 }

		
		-- 1.3.6.1.4.1.2011.6.122.15.1.1.2.4
		hwSecStatAlteration OBJECT-TYPE
			SYNTAX Integer32 (0..25)
			MAX-ACCESS read-write
			STATUS current
			DESCRIPTION
				"The proportion of change in the packets scale."
			::= { hwSecStatGlobalPktScale 4 }

		
		-- 1.3.6.1.4.1.2011.6.122.15.1.1.2.5
		hwSecStatCalcTime OBJECT-TYPE
			SYNTAX Integer32 (0..14400)
			MAX-ACCESS read-write
			STATUS current
			DESCRIPTION
				"The period of packet scale statistics, the unit is minute."
			::= { hwSecStatGlobalPktScale 5 }

		
		-- 1.3.6.1.4.1.2011.6.122.15.1.1.2.6
		hwSecStatPktScaleSetDefault OBJECT-TYPE
			SYNTAX Integer32 (0..1)
			MAX-ACCESS read-write
			STATUS current
			DESCRIPTION
				"
				This OID is used for setting the packet scale configuration to default.
				When you want to set the value to default, set this OID to 1.
				"
			::= { hwSecStatGlobalPktScale 6 }

		
		-- 1.3.6.1.4.1.2011.6.122.15.1.1.3
		hwSecStatGlobalSessNum OBJECT IDENTIFIER ::= { hwSecStatCfgObjects 3 }

		
		-- 1.3.6.1.4.1.2011.6.122.15.1.1.3.1
		hwSecStatTcpSessNumMax OBJECT-TYPE
			SYNTAX Integer32
			MAX-ACCESS read-write
			STATUS current
			DESCRIPTION
				"The maximun number of TCP session allowed."
			::= { hwSecStatGlobalSessNum 1 }

		-- 1.3.6.1.4.1.2011.6.122.15.1.1.3.2
		hwSecStatTcpSessNumMin OBJECT-TYPE
			SYNTAX Integer32
			MAX-ACCESS read-write
			STATUS current
			DESCRIPTION
				"
				The minimum of TCP session.
				when the number of TCP session in one system arrive the maximum allowed,
				system would decrease the TCP session by some method, 
				once the number of tcp session in one system arrive the minumim,
				system would stop decreasing the TCP session.
				"
			::= { hwSecStatGlobalSessNum 2 }

		
		-- 1.3.6.1.4.1.2011.6.122.15.1.1.3.3
		hwSecStatUdpSessNumMax OBJECT-TYPE
			SYNTAX Integer32
			MAX-ACCESS read-write
			STATUS current
			DESCRIPTION
				"The maximun number of UDP session allowed."
			::= { hwSecStatGlobalSessNum 3 }

		
		-- 1.3.6.1.4.1.2011.6.122.15.1.1.3.4
		hwSecStatUdpSessNumMin OBJECT-TYPE
			SYNTAX Integer32
			MAX-ACCESS read-write
			STATUS current
			DESCRIPTION
				"
				The minimum of UDP session.
				when the number of UDP session in one system arrive the maximum allowed,
				system would decrease the UDP session by some method, 
				once the number of tcp session in one system arrive the minumim,
				system would stop decreasing the UDP session.
				"
			::= { hwSecStatGlobalSessNum 4 }

		
		-- 1.3.6.1.4.1.2011.6.122.15.1.1.3.5
		hwSecStatGlobalSessSetDefault OBJECT-TYPE
			SYNTAX Integer32 (0..1)
			MAX-ACCESS read-write
			STATUS current
			DESCRIPTION
				"
				This OID is used for setting the global session number configuration to default.
				When you want to set the value to default, set this OID to 1.
				"
			::= { hwSecStatGlobalSessNum 5 }

		
		-- 1.3.6.1.4.1.2011.6.122.15.1.2
		hwSecStatMonitorObjects OBJECT IDENTIFIER ::= { hwSecStatGlobal 2 }

		
		-- 1.3.6.1.4.1.2011.6.122.15.1.2.1
		hwSecStatMonitorGlobalSessFlow OBJECT IDENTIFIER ::= { hwSecStatMonitorObjects 1 }

		
		-- 1.3.6.1.4.1.2011.6.122.15.1.2.1.1
		hwSecStatMonTotalBootConnNum OBJECT-TYPE
			SYNTAX Counter64
			MAX-ACCESS read-only
			STATUS current
			DESCRIPTION
				"
				The total number of connection since device startup.
				This number is increased only.
				"
			::= { hwSecStatMonitorGlobalSessFlow 1 }

		
		-- 1.3.6.1.4.1.2011.6.122.15.1.2.1.2
		hwSecStatMonPeakSessSpeed OBJECT-TYPE
			SYNTAX Counter64
			MAX-ACCESS read-only
			STATUS current
			DESCRIPTION
				"The maximun speed of session establishing since device startup."
			::= { hwSecStatMonitorGlobalSessFlow 2 }

		
		-- 1.3.6.1.4.1.2011.6.122.15.1.2.1.3
		hwSecStatMonCurSessSpeed OBJECT-TYPE
			SYNTAX Counter64
			MAX-ACCESS read-only
			STATUS current
			DESCRIPTION
				"The current speed of session establishing."
			::= { hwSecStatMonitorGlobalSessFlow 3 }

		
		-- 1.3.6.1.4.1.2011.6.122.15.1.2.1.4
		hwSecStatMonTotalSess OBJECT-TYPE
			SYNTAX Counter64
			MAX-ACCESS read-only
			STATUS current
			DESCRIPTION
				"The total session in the system currently."
			::= { hwSecStatMonitorGlobalSessFlow 4 }

		
		-- 1.3.6.1.4.1.2011.6.122.15.1.2.1.5
		hwSecStatMonHalfConn OBJECT-TYPE
			SYNTAX Counter64
			MAX-ACCESS read-only
			STATUS current
			DESCRIPTION
				"The number of incomplete session in system currently."
			::= { hwSecStatMonitorGlobalSessFlow 5 }

		
		-- 1.3.6.1.4.1.2011.6.122.15.1.2.1.6
		hwSecStatMonTcpSess OBJECT-TYPE
			SYNTAX Counter64
			MAX-ACCESS read-only
			STATUS current
			DESCRIPTION
				"The current number of TCP sessions."
			::= { hwSecStatMonitorGlobalSessFlow 6 }

		
		-- 1.3.6.1.4.1.2011.6.122.15.1.2.1.7
		hwSecStatMonUdpSess OBJECT-TYPE
			SYNTAX Counter64
			MAX-ACCESS read-only
			STATUS current
			DESCRIPTION
				"The current number of UDP sessions."
			::= { hwSecStatMonitorGlobalSessFlow 7 }

		
		-- 1.3.6.1.4.1.2011.6.122.15.1.2.1.8
		hwSecStatMonIcmpSess OBJECT-TYPE
			SYNTAX Counter64
			MAX-ACCESS read-only
			STATUS current
			DESCRIPTION
				"The current number of ICMP sessions."
			::= { hwSecStatMonitorGlobalSessFlow 8 }

		
		-- 1.3.6.1.4.1.2011.6.122.15.1.2.1.9
		hwSecStatMonSvrMapTblNum OBJECT-TYPE
			SYNTAX Counter64
			MAX-ACCESS read-only
			STATUS current
			DESCRIPTION
				"The total number of server map."
			::= { hwSecStatMonitorGlobalSessFlow 9 }

		
		-- 1.3.6.1.4.1.2011.6.122.15.1.2.1.10
		hwSecStatFragTblNum OBJECT-TYPE
			SYNTAX Counter64
			MAX-ACCESS read-only
			STATUS current
			DESCRIPTION
				"The number of entry in fragment table."
			::= { hwSecStatMonitorGlobalSessFlow 10 }

		
		-- 1.3.6.1.4.1.2011.6.122.15.1.2.1.11
		hwSecStatMonRcvIcmpPkts OBJECT-TYPE
			SYNTAX Counter64
			MAX-ACCESS read-only
			STATUS current
			DESCRIPTION
				"The total number of ICMP packets received by system."
			::= { hwSecStatMonitorGlobalSessFlow 11 }

		
		-- 1.3.6.1.4.1.2011.6.122.15.1.2.1.12
		hwSecStatMonRcvIcmpOcts OBJECT-TYPE
			SYNTAX Counter64
			MAX-ACCESS read-only
			STATUS current
			DESCRIPTION
				"The total bytes of ICMP packets received by system."
			::= { hwSecStatMonitorGlobalSessFlow 12 }

		
		-- 1.3.6.1.4.1.2011.6.122.15.1.2.1.13
		hwSecStatMonRcvTcpPkts OBJECT-TYPE
			SYNTAX Counter64
			MAX-ACCESS read-only
			STATUS current
			DESCRIPTION
				"The total number of TCP packets received by system."
			::= { hwSecStatMonitorGlobalSessFlow 13 }

		
		-- 1.3.6.1.4.1.2011.6.122.15.1.2.1.14
		hwSecStatMonRcvTcpOcts OBJECT-TYPE
			SYNTAX Counter64
			MAX-ACCESS read-only
			STATUS current
			DESCRIPTION
				"The total bytes of TCP packets received by system."
			::= { hwSecStatMonitorGlobalSessFlow 14 }

		
		-- 1.3.6.1.4.1.2011.6.122.15.1.2.1.15
		hwSecStatMonRcvUdpPkts OBJECT-TYPE
			SYNTAX Counter64
			MAX-ACCESS read-only
			STATUS current
			DESCRIPTION
				"The total number of UDP packets received by system."
			::= { hwSecStatMonitorGlobalSessFlow 15 }

		
		-- 1.3.6.1.4.1.2011.6.122.15.1.2.1.16
		hwSecStatMonRcvUdpOcts OBJECT-TYPE
			SYNTAX Counter64
			MAX-ACCESS read-only
			STATUS current
			DESCRIPTION
				"The total bytes of UDP packets received by system."
			::= { hwSecStatMonitorGlobalSessFlow 16 }

		
		-- 1.3.6.1.4.1.2011.6.122.15.1.2.1.17
		hwSecStatMonRcvEtcPkts OBJECT-TYPE
			SYNTAX Counter64
			MAX-ACCESS read-only
			STATUS current
			DESCRIPTION
				"The total number of other type packets received by system."
			::= { hwSecStatMonitorGlobalSessFlow 17 }

		
		-- 1.3.6.1.4.1.2011.6.122.15.1.2.1.18
		hwSecStatMonRcvEtcOcts OBJECT-TYPE
			SYNTAX Counter64
			MAX-ACCESS read-only
			STATUS current
			DESCRIPTION
				"The total bytes of other type packets received by system."
			::= { hwSecStatMonitorGlobalSessFlow 18 }

		
		-- 1.3.6.1.4.1.2011.6.122.15.1.2.1.19
		hwSecStatMonPassIcmpPkts OBJECT-TYPE
			SYNTAX Counter64
			MAX-ACCESS read-only
			STATUS current
			DESCRIPTION
				"The total number of ICMP packets pass the system."
			::= { hwSecStatMonitorGlobalSessFlow 19 }

		
		-- 1.3.6.1.4.1.2011.6.122.15.1.2.1.20
		hwSecStatMonPassIcmpOcts OBJECT-TYPE
			SYNTAX Counter64
			MAX-ACCESS read-only
			STATUS current
			DESCRIPTION
				"The total bytes of ICMP packets pass the system."
			::= { hwSecStatMonitorGlobalSessFlow 20 }

		
		-- 1.3.6.1.4.1.2011.6.122.15.1.2.1.21
		hwSecStatMonPassTcpPkts OBJECT-TYPE
			SYNTAX Counter64
			MAX-ACCESS read-only
			STATUS current
			DESCRIPTION
				"The total number of TCP packets pass the system."
			::= { hwSecStatMonitorGlobalSessFlow 21 }

		
		-- 1.3.6.1.4.1.2011.6.122.15.1.2.1.22
		hwSecStatMonPassTcpOcts OBJECT-TYPE
			SYNTAX Counter64
			MAX-ACCESS read-only
			STATUS current
			DESCRIPTION
				"The total bytes of TCP packets pass the system."
			::= { hwSecStatMonitorGlobalSessFlow 22 }

		
		-- 1.3.6.1.4.1.2011.6.122.15.1.2.1.23
		hwSecStatMonPassUdpPkts OBJECT-TYPE
			SYNTAX Counter64
			MAX-ACCESS read-only
			STATUS current
			DESCRIPTION
				"The total number of UDP packets pass the system."
			::= { hwSecStatMonitorGlobalSessFlow 23 }

		
		-- 1.3.6.1.4.1.2011.6.122.15.1.2.1.24
		hwSecStatMonPassUdpOcts OBJECT-TYPE
			SYNTAX Counter64
			MAX-ACCESS read-only
			STATUS current
			DESCRIPTION
				"The total bytes of UDP packets pass the system."
			::= { hwSecStatMonitorGlobalSessFlow 24 }

		
		-- 1.3.6.1.4.1.2011.6.122.15.1.2.1.25
		hwSecStatMonPassEtcPkts OBJECT-TYPE
			SYNTAX Counter64
			MAX-ACCESS read-only
			STATUS current
			DESCRIPTION
				"The total number of other type packets pass the system."
			::= { hwSecStatMonitorGlobalSessFlow 25 }

		
		-- 1.3.6.1.4.1.2011.6.122.15.1.2.1.26
		hwSecStatMonPassEtcOcts OBJECT-TYPE
			SYNTAX Counter64
			MAX-ACCESS read-only
			STATUS current
			DESCRIPTION
				"The total bytes of other type packets pass the system."
			::= { hwSecStatMonitorGlobalSessFlow 26 }

		
		-- 1.3.6.1.4.1.2011.6.122.15.1.2.1.27
		hwSecStatMonSynPkts OBJECT-TYPE
			SYNTAX Counter64
			MAX-ACCESS read-only
			STATUS current
			DESCRIPTION
				"The total number of SYN packets arriving the system."
			::= { hwSecStatMonitorGlobalSessFlow 27 }

		
		-- 1.3.6.1.4.1.2011.6.122.15.1.2.1.28
		hwSecStatMonFinPkts OBJECT-TYPE
			SYNTAX Counter64
			MAX-ACCESS read-only
			STATUS current
			DESCRIPTION
				"The total number of FIN packets arriving the system."
			::= { hwSecStatMonitorGlobalSessFlow 28 }

		
		-- 1.3.6.1.4.1.2011.6.122.15.1.2.1.29
		hwSecStatMonSynAckPkts OBJECT-TYPE
			SYNTAX Counter64
			MAX-ACCESS read-only
			STATUS current
			DESCRIPTION
				"The total number of SYN-ACK packets arriving the system."
			::= { hwSecStatMonitorGlobalSessFlow 29 }

		
		-- 1.3.6.1.4.1.2011.6.122.15.1.2.1.30
		hwSecStatMonRstPkts OBJECT-TYPE
			SYNTAX Counter64
			MAX-ACCESS read-only
			STATUS current
			DESCRIPTION
				"The total number of RESET packets arriving the system."
			::= { hwSecStatMonitorGlobalSessFlow 30 }

		
		-- 1.3.6.1.4.1.2011.6.122.15.1.2.1.31
		hwSecStatMonRcvFragPkts OBJECT-TYPE
			SYNTAX Counter64
			MAX-ACCESS read-only
			STATUS current
			DESCRIPTION
				"The total number of fragment packets arriving the system."
			::= { hwSecStatMonitorGlobalSessFlow 31 }

		
		-- 1.3.6.1.4.1.2011.6.122.15.1.2.1.32
		hwSecStatMonRcvFragOcts OBJECT-TYPE
			SYNTAX Counter64
			MAX-ACCESS read-only
			STATUS current
			DESCRIPTION
				"The total bytes of fragment packets arriving the system."
			::= { hwSecStatMonitorGlobalSessFlow 32 }

		
		-- 1.3.6.1.4.1.2011.6.122.15.1.2.1.33
		hwSecStatMonAllPkts OBJECT-TYPE
			SYNTAX Counter64
			MAX-ACCESS read-only
			STATUS current
			DESCRIPTION
				"The number of received packets by the device."
			::= { hwSecStatMonitorGlobalSessFlow 33 }

		
		-- 1.3.6.1.4.1.2011.6.122.15.1.2.1.34
		hwSecStatMonAllOcts OBJECT-TYPE
			SYNTAX Counter64
			MAX-ACCESS read-only
			STATUS current
			DESCRIPTION
				"The number of received bytes by the device."
			::= { hwSecStatMonitorGlobalSessFlow 34 }

		
		-- 1.3.6.1.4.1.2011.6.122.15.1.2.1.35
		hwSecStatClearGlobalSessFlowInfo OBJECT-TYPE
			SYNTAX Integer32 (0..1)
			MAX-ACCESS read-write
			STATUS current
			DESCRIPTION
				"
				Use this OID to clear the global session flow statistics information.
				When you want to clear the information, set this OID to 1.
				"
			::= { hwSecStatMonitorGlobalSessFlow 35 }

		
		-- 1.3.6.1.4.1.2011.6.122.15.1.2.1.36
		hwSecStatHisSessNumMax OBJECT-TYPE
			SYNTAX Counter64
			MAX-ACCESS read-only
			STATUS current
			DESCRIPTION
				"The maximun number of session in history"
			::= { hwSecStatMonitorGlobalSessFlow 36 }

		
		-- 1.3.6.1.4.1.2011.6.122.15.1.2.2
		hwSecStatMonitorGlobalAppInfo OBJECT IDENTIFIER ::= { hwSecStatMonitorObjects 2 }

		
		-- 1.3.6.1.4.1.2011.6.122.15.1.2.2.1
		hwSecStatMonFtpSessions OBJECT-TYPE
			SYNTAX Counter64
			MAX-ACCESS read-only
			STATUS current
			DESCRIPTION
				"The total number of FTP sessions in the system currently."
			::= { hwSecStatMonitorGlobalAppInfo 1 }

		
		-- 1.3.6.1.4.1.2011.6.122.15.1.2.2.2
		hwSecStatMonRcvFtpPkts OBJECT-TYPE
			SYNTAX Counter64
			MAX-ACCESS read-only
			STATUS current
			DESCRIPTION
				"The total number of FTP packets received by system."
			::= { hwSecStatMonitorGlobalAppInfo 2 }

		
		-- 1.3.6.1.4.1.2011.6.122.15.1.2.2.3
		hwSecStatMonRcvFtpOcts OBJECT-TYPE
			SYNTAX Counter64
			MAX-ACCESS read-only
			STATUS current
			DESCRIPTION
				"The total bytes of FTP packets received by system."
			::= { hwSecStatMonitorGlobalAppInfo 3 }

		
		-- 1.3.6.1.4.1.2011.6.122.15.1.2.2.4
		hwSecStatMonSmtpSessions OBJECT-TYPE
			SYNTAX Counter64
			MAX-ACCESS read-only
			STATUS current
			DESCRIPTION
				"The total number of SMTP sessions in the system currently."
			::= { hwSecStatMonitorGlobalAppInfo 4 }

		
		-- 1.3.6.1.4.1.2011.6.122.15.1.2.2.5
		hwSecStatMonRcvSmtpPkts OBJECT-TYPE
			SYNTAX Counter64
			MAX-ACCESS read-only
			STATUS current
			DESCRIPTION
				"The total number of SMTP packets received by system."
			::= { hwSecStatMonitorGlobalAppInfo 5 }

		
		-- 1.3.6.1.4.1.2011.6.122.15.1.2.2.6
		hwSecStatMonRcvSmtpOcts OBJECT-TYPE
			SYNTAX Counter64
			MAX-ACCESS read-only
			STATUS current
			DESCRIPTION
				"The total bytes of SMTP packets received by system."
			::= { hwSecStatMonitorGlobalAppInfo 6 }

		
		-- 1.3.6.1.4.1.2011.6.122.15.1.2.2.7
		hwSecStatMonHttpSessions OBJECT-TYPE
			SYNTAX Counter64
			MAX-ACCESS read-only
			STATUS current
			DESCRIPTION
				"The total number of HTTP sessions in the system currently."
			::= { hwSecStatMonitorGlobalAppInfo 7 }

		
		-- 1.3.6.1.4.1.2011.6.122.15.1.2.2.8
		hwSecStatMonRcvHttpPkts OBJECT-TYPE
			SYNTAX Counter64
			MAX-ACCESS read-only
			STATUS current
			DESCRIPTION
				"The total number of HTTP packets received by system."
			::= { hwSecStatMonitorGlobalAppInfo 8 }

		
		-- 1.3.6.1.4.1.2011.6.122.15.1.2.2.9
		hwSecStatMonRcvHttpOcts OBJECT-TYPE
			SYNTAX Counter64
			MAX-ACCESS read-only
			STATUS current
			DESCRIPTION
				"The total bytes of HTTP packets received by system."
			::= { hwSecStatMonitorGlobalAppInfo 9 }

		
		-- 1.3.6.1.4.1.2011.6.122.15.1.2.2.10
		hwSecStatMonH323Sessions OBJECT-TYPE
			SYNTAX Counter64
			MAX-ACCESS read-only
			STATUS current
			DESCRIPTION
				"The total number of H323 sessions in the system currently."
			::= { hwSecStatMonitorGlobalAppInfo 10 }

		
		-- 1.3.6.1.4.1.2011.6.122.15.1.2.2.11
		hwSecStatMonRcvH323Pkts OBJECT-TYPE
			SYNTAX Counter64
			MAX-ACCESS read-only
			STATUS current
			DESCRIPTION
				"The total number of H323 packets received by system."
			::= { hwSecStatMonitorGlobalAppInfo 11 }

		
		-- 1.3.6.1.4.1.2011.6.122.15.1.2.2.12
		hwSecStatMonRcvH323Octs OBJECT-TYPE
			SYNTAX Counter64
			MAX-ACCESS read-only
			STATUS current
			DESCRIPTION
				"The total bytes of H323 packets received by system."
			::= { hwSecStatMonitorGlobalAppInfo 12 }

		
		-- 1.3.6.1.4.1.2011.6.122.15.1.2.2.13
		hwSecStatMonRtspSessions OBJECT-TYPE
			SYNTAX Counter64
			MAX-ACCESS read-only
			STATUS current
			DESCRIPTION
				"The total number of RTSP sessions in the system currently."
			::= { hwSecStatMonitorGlobalAppInfo 13 }

		
		-- 1.3.6.1.4.1.2011.6.122.15.1.2.2.14
		hwSecStatMonRcvRtspPkts OBJECT-TYPE
			SYNTAX Counter64
			MAX-ACCESS read-only
			STATUS current
			DESCRIPTION
				"The total number of RTSP packets received by system."
			::= { hwSecStatMonitorGlobalAppInfo 14 }

		-- 1.3.6.1.4.1.2011.6.122.15.1.2.2.15
		hwSecStatMonRcvRtspOcts OBJECT-TYPE
			SYNTAX Counter64
			MAX-ACCESS read-only
			STATUS current
			DESCRIPTION
				"The total bytes of RTSP packets received by system."
			::= { hwSecStatMonitorGlobalAppInfo 15 }

		
		-- 1.3.6.1.4.1.2011.6.122.15.1.2.2.16
		hwSecStatMonDnsSessions OBJECT-TYPE
			SYNTAX Counter64
			MAX-ACCESS read-only
			STATUS current
			DESCRIPTION
				"The total number of DNS sessions in the system currently."
			::= { hwSecStatMonitorGlobalAppInfo 16 }

		
		-- 1.3.6.1.4.1.2011.6.122.15.1.2.2.17
		hwSecStatMonRcvDnsPkts OBJECT-TYPE
			SYNTAX Counter64
			MAX-ACCESS read-only
			STATUS current
			DESCRIPTION
				"The total number of DNS packets received by system."
			::= { hwSecStatMonitorGlobalAppInfo 17 }

		
		-- 1.3.6.1.4.1.2011.6.122.15.1.2.2.18
		hwSecStatMonRcvDnsOcts OBJECT-TYPE
			SYNTAX Counter64
			MAX-ACCESS read-only
			STATUS current
			DESCRIPTION
				"The total bytes of DNS packets received by system."
			::= { hwSecStatMonitorGlobalAppInfo 18 }

		
		-- 1.3.6.1.4.1.2011.6.122.15.1.2.2.19
		hwSecStatMonGtpSessions OBJECT-TYPE
			SYNTAX Counter64
			MAX-ACCESS read-only
			STATUS current
			DESCRIPTION
				"The total number of Gtp sessions in the system currently."
			::= { hwSecStatMonitorGlobalAppInfo 19 }

		
		-- 1.3.6.1.4.1.2011.6.122.15.1.2.2.20
		hwSecStatMonRcvGtpPkts OBJECT-TYPE
			SYNTAX Counter64
			MAX-ACCESS read-only
			STATUS current
			DESCRIPTION
				"The total number of Gtp packets received by system."
			::= { hwSecStatMonitorGlobalAppInfo 20 }

		
		-- 1.3.6.1.4.1.2011.6.122.15.1.2.2.21
		hwSecStatMonRcvGtpOcts OBJECT-TYPE
			SYNTAX Counter64
			MAX-ACCESS read-only
			STATUS current
			DESCRIPTION
				"The total bytes of Gtp packets received by system."
			::= { hwSecStatMonitorGlobalAppInfo 21 }

		
		-- 1.3.6.1.4.1.2011.6.122.15.1.2.2.22
		hwSecStatMonHwccSessions OBJECT-TYPE
			SYNTAX Counter64
			MAX-ACCESS read-only
			STATUS current
			DESCRIPTION
				"The total number of Hwcc sessions in the system currently."
			::= { hwSecStatMonitorGlobalAppInfo 22 }

		
		-- 1.3.6.1.4.1.2011.6.122.15.1.2.2.23
		hwSecStatMonRcvHwccPkts OBJECT-TYPE
			SYNTAX Counter64
			MAX-ACCESS read-only
			STATUS current
			DESCRIPTION
				"The total number of Hwcc packets received by system."
			::= { hwSecStatMonitorGlobalAppInfo 23 }

		
		-- 1.3.6.1.4.1.2011.6.122.15.1.2.2.24
		hwSecStatMonRcvHwccOcts OBJECT-TYPE
			SYNTAX Counter64
			MAX-ACCESS read-only
			STATUS current
			DESCRIPTION
				"The total bytes of Hwcc packets received by system."
			::= { hwSecStatMonitorGlobalAppInfo 24 }

		
		-- 1.3.6.1.4.1.2011.6.122.15.1.2.2.25
		hwSecStatMonIlsSessions OBJECT-TYPE
			SYNTAX Counter64
			MAX-ACCESS read-only
			STATUS current
			DESCRIPTION
				"The total number of Ils sessions in the system currently."
			::= { hwSecStatMonitorGlobalAppInfo 25 }

		
		-- 1.3.6.1.4.1.2011.6.122.15.1.2.2.26
		hwSecStatMonRcvIlsPkts OBJECT-TYPE
			SYNTAX Counter64
			MAX-ACCESS read-only
			STATUS current
			DESCRIPTION
				"The total number of Ils packets received by system."
			::= { hwSecStatMonitorGlobalAppInfo 26 }

		
		-- 1.3.6.1.4.1.2011.6.122.15.1.2.2.27
		hwSecStatMonRcvIlsOcts OBJECT-TYPE
			SYNTAX Counter64
			MAX-ACCESS read-only
			STATUS current
			DESCRIPTION
				"The total bytes of Ils packets received by system."
			::= { hwSecStatMonitorGlobalAppInfo 27 }

		
		-- 1.3.6.1.4.1.2011.6.122.15.1.2.2.28
		hwSecStatMonMgcpSessions OBJECT-TYPE
			SYNTAX Counter64
			MAX-ACCESS read-only
			STATUS current
			DESCRIPTION
				"The total number of Mgcp sessions in the system currently."
			::= { hwSecStatMonitorGlobalAppInfo 28 }

		
		-- 1.3.6.1.4.1.2011.6.122.15.1.2.2.29
		hwSecStatMonRcvMgcpPkts OBJECT-TYPE
			SYNTAX Counter64
			MAX-ACCESS read-only
			STATUS current
			DESCRIPTION
				"The total number of Mgcp packets received by system."
			::= { hwSecStatMonitorGlobalAppInfo 29 }

		
		-- 1.3.6.1.4.1.2011.6.122.15.1.2.2.30
		hwSecStatMonRcvMgcpOcts OBJECT-TYPE
			SYNTAX Counter64
			MAX-ACCESS read-only
			STATUS current
			DESCRIPTION
				"The total bytes of Mgcp packets received by system."
			::= { hwSecStatMonitorGlobalAppInfo 30 }

		
		-- 1.3.6.1.4.1.2011.6.122.15.1.2.2.31
		hwSecStatMonMmsSessions OBJECT-TYPE
			SYNTAX Counter64
			MAX-ACCESS read-only
			STATUS current
			DESCRIPTION
				"The total number of Mms sessions in the system currently."
			::= { hwSecStatMonitorGlobalAppInfo 31 }

		
		-- 1.3.6.1.4.1.2011.6.122.15.1.2.2.32
		hwSecStatMonRcvMmsPkts OBJECT-TYPE
			SYNTAX Counter64
			MAX-ACCESS read-only
			STATUS current
			DESCRIPTION
				"The total number of Mms packets received by system."
			::= { hwSecStatMonitorGlobalAppInfo 32 }

		
		-- 1.3.6.1.4.1.2011.6.122.15.1.2.2.33
		hwSecStatMonRcvMmsOcts OBJECT-TYPE
			SYNTAX Counter64
			MAX-ACCESS read-only
			STATUS current
			DESCRIPTION
				"The total bytes of Mms packets received by system."
			::= { hwSecStatMonitorGlobalAppInfo 33 }

		
		-- 1.3.6.1.4.1.2011.6.122.15.1.2.2.34
		hwSecStatMonNbtSessions OBJECT-TYPE
			SYNTAX Counter64
			MAX-ACCESS read-only
			STATUS current
			DESCRIPTION
				"The total number of Nbt sessions in the system currently."
			::= { hwSecStatMonitorGlobalAppInfo 34 }

		
		-- 1.3.6.1.4.1.2011.6.122.15.1.2.2.35
		hwSecStatMonRcvNbtPkts OBJECT-TYPE
			SYNTAX Counter64
			MAX-ACCESS read-only
			STATUS current
			DESCRIPTION
				"The total number of Nbt packets received by system."
			::= { hwSecStatMonitorGlobalAppInfo 35 }

		
		-- 1.3.6.1.4.1.2011.6.122.15.1.2.2.36
		hwSecStatMonRcvNbtOcts OBJECT-TYPE
			SYNTAX Counter64
			MAX-ACCESS read-only
			STATUS current
			DESCRIPTION
				"The total bytes of Nbt packets received by system."
			::= { hwSecStatMonitorGlobalAppInfo 36 }

		
		-- 1.3.6.1.4.1.2011.6.122.15.1.2.2.37
		hwSecStatMonPptpSessions OBJECT-TYPE
			SYNTAX Counter64
			MAX-ACCESS read-only
			STATUS current
			DESCRIPTION
				"The total number of Pptp sessions in the system currently."
			::= { hwSecStatMonitorGlobalAppInfo 37 }

		
		-- 1.3.6.1.4.1.2011.6.122.15.1.2.2.38
		hwSecStatMonRcvPptpPkts OBJECT-TYPE
			SYNTAX Counter64
			MAX-ACCESS read-only
			STATUS current
			DESCRIPTION
				"The total number of Pptp packets received by system."
			::= { hwSecStatMonitorGlobalAppInfo 38 }

		
		-- 1.3.6.1.4.1.2011.6.122.15.1.2.2.39
		hwSecStatMonRcvPptpOcts OBJECT-TYPE
			SYNTAX Counter64
			MAX-ACCESS read-only
			STATUS current
			DESCRIPTION
				"The total bytes of Pptp packets received by system."
			::= { hwSecStatMonitorGlobalAppInfo 39 }

		
		-- 1.3.6.1.4.1.2011.6.122.15.1.2.2.40
		hwSecStatMonQQSessions OBJECT-TYPE
			SYNTAX Counter64
			MAX-ACCESS read-only
			STATUS current
			DESCRIPTION
				"The total number of QQ sessions in the system currently."
			::= { hwSecStatMonitorGlobalAppInfo 40 }

		
		-- 1.3.6.1.4.1.2011.6.122.15.1.2.2.41
		hwSecStatMonRcvQQPkts OBJECT-TYPE
			SYNTAX Counter64
			MAX-ACCESS read-only
			STATUS current
			DESCRIPTION
				"The total number of QQ packets received by system."
			::= { hwSecStatMonitorGlobalAppInfo 41 }

		
		-- 1.3.6.1.4.1.2011.6.122.15.1.2.2.42
		hwSecStatMonRcvQQOcts OBJECT-TYPE
			SYNTAX Counter64
			MAX-ACCESS read-only
			STATUS current
			DESCRIPTION
				"The total bytes of QQ packets received by system."
			::= { hwSecStatMonitorGlobalAppInfo 42 }

		
		-- 1.3.6.1.4.1.2011.6.122.15.1.2.2.43
		hwSecStatMonRasSessions OBJECT-TYPE
			SYNTAX Counter64
			MAX-ACCESS read-only
			STATUS current
			DESCRIPTION
				"The total number of Ras sessions in the system currently."
			::= { hwSecStatMonitorGlobalAppInfo 43 }

		
		-- 1.3.6.1.4.1.2011.6.122.15.1.2.2.44
		hwSecStatMonRcvRasPkts OBJECT-TYPE
			SYNTAX Counter64
			MAX-ACCESS read-only
			STATUS current
			DESCRIPTION
				"The total number of Ras packets received by system."
			::= { hwSecStatMonitorGlobalAppInfo 44 }

		
		-- 1.3.6.1.4.1.2011.6.122.15.1.2.2.45
		hwSecStatMonRcvRasOcts OBJECT-TYPE
			SYNTAX Counter64
			MAX-ACCESS read-only
			STATUS current
			DESCRIPTION
				"The total bytes of Ras packets received by system."
			::= { hwSecStatMonitorGlobalAppInfo 45 }

		
		-- 1.3.6.1.4.1.2011.6.122.15.1.2.2.46
		hwSecStatMonRpcSessions OBJECT-TYPE
			SYNTAX Counter64
			MAX-ACCESS read-only
			STATUS current
			DESCRIPTION
				"The total number of Rpc sessions in the system currently."
			::= { hwSecStatMonitorGlobalAppInfo 46 }

		
		-- 1.3.6.1.4.1.2011.6.122.15.1.2.2.47
		hwSecStatMonRcvRpcPkts OBJECT-TYPE
			SYNTAX Counter64
			MAX-ACCESS read-only
			STATUS current
			DESCRIPTION
				"The total number of Rpc packets received by system."
			::= { hwSecStatMonitorGlobalAppInfo 47 }

		
		-- 1.3.6.1.4.1.2011.6.122.15.1.2.2.48
		hwSecStatMonRcvRpcOcts OBJECT-TYPE
			SYNTAX Counter64
			MAX-ACCESS read-only
			STATUS current
			DESCRIPTION
				"The total bytes of Rpc packets received by system."
			::= { hwSecStatMonitorGlobalAppInfo 48 }

		
		-- 1.3.6.1.4.1.2011.6.122.15.1.2.2.49
		hwSecStatMonSipSessions OBJECT-TYPE
			SYNTAX Counter64
			MAX-ACCESS read-only
			STATUS current
			DESCRIPTION
				"The total number of Sip sessions in the system currently."
			::= { hwSecStatMonitorGlobalAppInfo 49 }

		
		-- 1.3.6.1.4.1.2011.6.122.15.1.2.2.50
		hwSecStatMonRcvSipPkts OBJECT-TYPE
			SYNTAX Counter64
			MAX-ACCESS read-only
			STATUS current
			DESCRIPTION
				"The total number of Sip packets received by system."
			::= { hwSecStatMonitorGlobalAppInfo 50 }

		
		-- 1.3.6.1.4.1.2011.6.122.15.1.2.2.51
		hwSecStatMonRcvSipOcts OBJECT-TYPE
			SYNTAX Counter64
			MAX-ACCESS read-only
			STATUS current
			DESCRIPTION
				"The total bytes of Sip packets received by system."
			::= { hwSecStatMonitorGlobalAppInfo 51 }

		
		-- 1.3.6.1.4.1.2011.6.122.15.1.2.2.52
		hwSecStatMonSqlnetSessions OBJECT-TYPE
			SYNTAX Counter64
			MAX-ACCESS read-only
			STATUS current
			DESCRIPTION
				"The total number of Sqlnet sessions in the system currently."
			::= { hwSecStatMonitorGlobalAppInfo 52 }

		
		-- 1.3.6.1.4.1.2011.6.122.15.1.2.2.53
		hwSecStatMonRcvSqlnetPkts OBJECT-TYPE
			SYNTAX Counter64
			MAX-ACCESS read-only
			STATUS current
			DESCRIPTION
				"The total number of Sqlnet packets received by system."
			::= { hwSecStatMonitorGlobalAppInfo 53 }

		
		-- 1.3.6.1.4.1.2011.6.122.15.1.2.2.54
		hwSecStatMonRcvSqlnetOcts OBJECT-TYPE
			SYNTAX Counter64
			MAX-ACCESS read-only
			STATUS current
			DESCRIPTION
				"The total bytes of Sqlnet packets received by system."
			::= { hwSecStatMonitorGlobalAppInfo 54 }

		
		-- 1.3.6.1.4.1.2011.6.122.15.1.2.2.55
		hwSecStatMonStunSessions OBJECT-TYPE
			SYNTAX Counter64
			MAX-ACCESS read-only
			STATUS current
			DESCRIPTION
				"The total number of Stun sessions in the system currently."
			::= { hwSecStatMonitorGlobalAppInfo 55 }

		
		-- 1.3.6.1.4.1.2011.6.122.15.1.2.2.56
		hwSecStatMonRcvStunPkts OBJECT-TYPE
			SYNTAX Counter64
			MAX-ACCESS read-only
			STATUS current
			DESCRIPTION
				"The total number of Stun packets received by system."
			::= { hwSecStatMonitorGlobalAppInfo 56 }

		
		-- 1.3.6.1.4.1.2011.6.122.15.1.2.2.57
		hwSecStatMonRcvStunOcts OBJECT-TYPE
			SYNTAX Counter64
			MAX-ACCESS read-only
			STATUS current
			DESCRIPTION
				"The total bytes of Stun packets received by system."
			::= { hwSecStatMonitorGlobalAppInfo 57 }

		
		-- 1.3.6.1.4.1.2011.6.122.15.1.2.2.58
		hwSecStatMonJavaAtckNum OBJECT-TYPE
			SYNTAX Counter64
			MAX-ACCESS read-only
			STATUS current
			DESCRIPTION
				"The number of JAVA attack detected by system."
			::= { hwSecStatMonitorGlobalAppInfo 58 }

		
		-- 1.3.6.1.4.1.2011.6.122.15.1.2.2.59
		hwSecStatClearGlobalAppInfo OBJECT-TYPE
			SYNTAX Integer32 (0..1)
			MAX-ACCESS read-write
			STATUS current
			DESCRIPTION
				"
				Use this OID to clear the global application statistics information.
				When you want to clear the information, set this OID to 1.
				"
			::= { hwSecStatMonitorGlobalAppInfo 59 }

		
		-- 1.3.6.1.4.1.2011.6.122.15.1.2.3
		hwSecStatMonitorGlobalDrop OBJECT IDENTIFIER ::= { hwSecStatMonitorObjects 3 }

		
		-- 1.3.6.1.4.1.2011.6.122.15.1.2.3.1
		hwSecStatNoSessTblPkts OBJECT-TYPE
			SYNTAX Counter64
			MAX-ACCESS read-only
			STATUS current
			DESCRIPTION
				"The total number of packets dropped for no session."
			::= { hwSecStatMonitorGlobalDrop 1 }

		
		-- 1.3.6.1.4.1.2011.6.122.15.1.2.3.2
		hwSecStatNoSessTblOcts OBJECT-TYPE
			SYNTAX Counter64
			MAX-ACCESS read-only
			STATUS current
			DESCRIPTION
				"The total bytes of packets dropped for no session."
			::= { hwSecStatMonitorGlobalDrop 2 }

		
		-- 1.3.6.1.4.1.2011.6.122.15.1.2.3.3
		hwSecStatSeqErrPkts OBJECT-TYPE
			SYNTAX Counter64
			MAX-ACCESS read-only
			STATUS current
			DESCRIPTION
				"The total number of packets dropped for sequence number error."
			::= { hwSecStatMonitorGlobalDrop 3 }

		
		-- 1.3.6.1.4.1.2011.6.122.15.1.2.3.4
		hwSecStatSeqErrOcts OBJECT-TYPE
			SYNTAX Counter64
			MAX-ACCESS read-only
			STATUS current
			DESCRIPTION
				"The total bytes of packets dropped for sequence number error."
			::= { hwSecStatMonitorGlobalDrop 4 }

		
		-- 1.3.6.1.4.1.2011.6.122.15.1.2.3.5
		hwSecStatAclDenyNonIcmpPkts OBJECT-TYPE
			SYNTAX Counter64
			MAX-ACCESS read-only
			STATUS current
			DESCRIPTION
				"The total number of non ICMP packets denied for acl rule."
			::= { hwSecStatMonitorGlobalDrop 5 }

		
		-- 1.3.6.1.4.1.2011.6.122.15.1.2.3.6
		hwSecStatAclDenyNonIcmpOcts OBJECT-TYPE
			SYNTAX Counter64
			MAX-ACCESS read-only
			STATUS current
			DESCRIPTION
				"The total bytes of non ICMP packets denied for acl rule."
			::= { hwSecStatMonitorGlobalDrop 6 }

		
		-- 1.3.6.1.4.1.2011.6.122.15.1.2.3.7
		hwSecStatAclDenyIcmpPkts OBJECT-TYPE
			SYNTAX Counter64
			MAX-ACCESS read-only
			STATUS current
			DESCRIPTION
				"The total number of ICMP packets denied by acl rule."
			::= { hwSecStatMonitorGlobalDrop 7 }

		
		-- 1.3.6.1.4.1.2011.6.122.15.1.2.3.8
		hwSecStatAclDenyIcmpOcts OBJECT-TYPE
			SYNTAX Counter64
			MAX-ACCESS read-only
			STATUS current
			DESCRIPTION
				"The total bytes of ICMP packets denied by acl rule."
			::= { hwSecStatMonitorGlobalDrop 8 }

		
		-- 1.3.6.1.4.1.2011.6.122.15.1.2.3.9
		hwSecStatBlsDenyPkts OBJECT-TYPE
			SYNTAX Counter64
			MAX-ACCESS read-only
			STATUS current
			DESCRIPTION
				"The total number of packets denied by blacklist."
			::= { hwSecStatMonitorGlobalDrop 9 }

		
		-- 1.3.6.1.4.1.2011.6.122.15.1.2.3.10
		hwSecStatBlsDenyOcts OBJECT-TYPE
			SYNTAX Counter64
			MAX-ACCESS read-only
			STATUS current
			DESCRIPTION
				"The total bytes of packets denied by blacklist."
			::= { hwSecStatMonitorGlobalDrop 10 }

		
		-- 1.3.6.1.4.1.2011.6.122.15.1.2.3.11
		hwSecStatIcmpFloodDropPkts OBJECT-TYPE
			SYNTAX Counter64
			MAX-ACCESS read-only
			STATUS current
			DESCRIPTION
				"The total number of packets dropped due to ICMP Flood attack."
			::= { hwSecStatMonitorGlobalDrop 11 }

		
		-- 1.3.6.1.4.1.2011.6.122.15.1.2.3.12
		hwSecStatIcmpFloodDropOcts OBJECT-TYPE
			SYNTAX Counter64
			MAX-ACCESS read-only
			STATUS current
			DESCRIPTION
				"The total bytes of packets dropped due to ICMP Flood attack."
			::= { hwSecStatMonitorGlobalDrop 12 }

		
		-- 1.3.6.1.4.1.2011.6.122.15.1.2.3.13
		hwSecStatUdpFloodDropPkts OBJECT-TYPE
			SYNTAX Counter64
			MAX-ACCESS read-only
			STATUS current
			DESCRIPTION
				"The total number of packets dropped due to UDP Flood attack."
			::= { hwSecStatMonitorGlobalDrop 13 }

		
		-- 1.3.6.1.4.1.2011.6.122.15.1.2.3.14
		hwSecStatUdpFloodDropOcts OBJECT-TYPE
			SYNTAX Counter64
			MAX-ACCESS read-only
			STATUS current
			DESCRIPTION
				"The total bytes of packets dropped due to UDP Flood attack."
			::= { hwSecStatMonitorGlobalDrop 14 }

		
		-- 1.3.6.1.4.1.2011.6.122.15.1.2.3.15
		hwSecStatAlgDropPkts OBJECT-TYPE
			SYNTAX Counter64
			MAX-ACCESS read-only
			STATUS current
			DESCRIPTION
				"The total number of packets dropped by application layer gateway."
			::= { hwSecStatMonitorGlobalDrop 15 }

		
		-- 1.3.6.1.4.1.2011.6.122.15.1.2.3.16
		hwSecStatAlgDropOcts OBJECT-TYPE
			SYNTAX Counter64
			MAX-ACCESS read-only
			STATUS current
			DESCRIPTION
				"The total bytes of packets dropped by application layer gateway."
			::= { hwSecStatMonitorGlobalDrop 16 }

		
		-- 1.3.6.1.4.1.2011.6.122.15.1.2.3.17
		hwSecStatIPVerErrDropPkts OBJECT-TYPE
			SYNTAX Counter64
			MAX-ACCESS read-only
			STATUS current
			DESCRIPTION
				"The total number of packets dropped for IP version error."
			::= { hwSecStatMonitorGlobalDrop 17 }

		
		-- 1.3.6.1.4.1.2011.6.122.15.1.2.3.18
		hwSecStatIpCrcDropPkts OBJECT-TYPE
			SYNTAX Counter64
			MAX-ACCESS read-only
			STATUS current
			DESCRIPTION
				"The total number of packets dropped for CRC error."
			::= { hwSecStatMonitorGlobalDrop 18 }

		
		-- 1.3.6.1.4.1.2011.6.122.15.1.2.3.19
		hwSecStatIpTTLDropPkts OBJECT-TYPE
			SYNTAX Counter64
			MAX-ACCESS read-only
			STATUS current
			DESCRIPTION
				"The total number of packets dropped for TTL error."
			::= { hwSecStatMonitorGlobalDrop 19 }

		
		-- 1.3.6.1.4.1.2011.6.122.15.1.2.3.20
		hwSecStatProtoErrDropPkts OBJECT-TYPE
			SYNTAX Counter64
			MAX-ACCESS read-only
			STATUS current
			DESCRIPTION
				"The total number of packets dropped for protocol error."
			::= { hwSecStatMonitorGlobalDrop 20 }

		
		-- 1.3.6.1.4.1.2011.6.122.15.1.2.3.21
		hwSecStatFragExcessDropPkts OBJECT-TYPE
			SYNTAX Counter64
			MAX-ACCESS read-only
			STATUS current
			DESCRIPTION
				"The total number of packets dropped by fragement exceed."
			::= { hwSecStatMonitorGlobalDrop 21 }

		
		-- 1.3.6.1.4.1.2011.6.122.15.1.2.3.22
		hwSecStatFragExcessDropOcts OBJECT-TYPE
			SYNTAX Counter64
			MAX-ACCESS read-only
			STATUS current
			DESCRIPTION
				"The total bytes of packets dropped by fragement exceed."
			::= { hwSecStatMonitorGlobalDrop 22 }

		
		-- 1.3.6.1.4.1.2011.6.122.15.1.2.3.23
		hwSecStatSessFailDropPkts OBJECT-TYPE
			SYNTAX Counter64
			MAX-ACCESS read-only
			STATUS current
			DESCRIPTION
				"The total number of packets dropped by session faild."
			::= { hwSecStatMonitorGlobalDrop 23 }

		
		-- 1.3.6.1.4.1.2011.6.122.15.1.2.3.24
		hwSecStatSessFailDropOcts OBJECT-TYPE
			SYNTAX Counter64
			MAX-ACCESS read-only
			STATUS current
			DESCRIPTION
				"The total bytes of packets dropped by session faild."
			::= { hwSecStatMonitorGlobalDrop 24 }

		
		-- 1.3.6.1.4.1.2011.6.122.15.1.2.3.25
		hwSecStatSynFloodDropPkts OBJECT-TYPE
			SYNTAX Counter64
			MAX-ACCESS read-only
			STATUS current
			DESCRIPTION
				"The total number of packets dropped due to SYN Flood attack."
			::= { hwSecStatMonitorGlobalDrop 25 }

		
		-- 1.3.6.1.4.1.2011.6.122.15.1.2.3.26
		hwSecStatSynFloodDropOcts OBJECT-TYPE
			SYNTAX Counter64
			MAX-ACCESS read-only
			STATUS current
			DESCRIPTION
				"The total bytes of packets dropped due to SYN Flood attack."
			::= { hwSecStatMonitorGlobalDrop 26 }

		
		-- 1.3.6.1.4.1.2011.6.122.15.1.2.3.27
		hwSecStatTcpFloodDropPkts OBJECT-TYPE
			SYNTAX Counter64
			MAX-ACCESS read-only
			STATUS current
			DESCRIPTION
				"The total number of packets dropped due to TCP Flood attack."
			::= { hwSecStatMonitorGlobalDrop 27 }

		
		-- 1.3.6.1.4.1.2011.6.122.15.1.2.3.28
		hwSecStatTcpFloodDropOcts OBJECT-TYPE
			SYNTAX Counter64
			MAX-ACCESS read-only
			STATUS current
			DESCRIPTION
				"The total bytes of packets dropped due to TCP Flood attack."
			::= { hwSecStatMonitorGlobalDrop 28 }

		
		-- 1.3.6.1.4.1.2011.6.122.15.1.2.3.29
		hwSecStatDnsFloodDropPkts OBJECT-TYPE
			SYNTAX Counter64
			MAX-ACCESS read-only
			STATUS current
			DESCRIPTION
				"The total number of packets dropped due to DNS Flood attack."
			::= { hwSecStatMonitorGlobalDrop 29 }

		
		-- 1.3.6.1.4.1.2011.6.122.15.1.2.3.30
		hwSecStatDnsFloodDropOcts OBJECT-TYPE
			SYNTAX Counter64
			MAX-ACCESS read-only
			STATUS current
			DESCRIPTION
				"The total bytes of packets dropped due to DNS Flood attack."
			::= { hwSecStatMonitorGlobalDrop 30 }

		
		-- 1.3.6.1.4.1.2011.6.122.15.1.2.3.31
		hwSecStatIpSweepDropPkts OBJECT-TYPE
			SYNTAX Counter64
			MAX-ACCESS read-only
			STATUS current
			DESCRIPTION
				"The total number of packets dropped due to ip sweep."
			::= { hwSecStatMonitorGlobalDrop 31 }

		
		-- 1.3.6.1.4.1.2011.6.122.15.1.2.3.32
		hwSecStatIpSweepDropOcts OBJECT-TYPE
			SYNTAX Counter64
			MAX-ACCESS read-only
			STATUS current
			DESCRIPTION
				"The total bytes of packets dropped due to ip sweep."
			::= { hwSecStatMonitorGlobalDrop 32 }

		
		-- 1.3.6.1.4.1.2011.6.122.15.1.2.3.33
		hwSecStatPortScanDropPkts OBJECT-TYPE
			SYNTAX Counter64
			MAX-ACCESS read-only
			STATUS current
			DESCRIPTION
				"The total number of packets dropped due to Port-scan."
			::= { hwSecStatMonitorGlobalDrop 33 }

		
		-- 1.3.6.1.4.1.2011.6.122.15.1.2.3.34
		hwSecStatPortScanDropocts OBJECT-TYPE
			SYNTAX Counter64
			MAX-ACCESS read-only
			STATUS current
			DESCRIPTION
				"The total bytes of packets dropped due to Port-scan."
			::= { hwSecStatMonitorGlobalDrop 34 }

		
		-- 1.3.6.1.4.1.2011.6.122.15.1.2.3.35
		hwSecStatLargeIcmpDropPkts OBJECT-TYPE
			SYNTAX Counter64
			MAX-ACCESS read-only
			STATUS current
			DESCRIPTION
				"The total number of packets dropped due to Large Icmp attack."
			::= { hwSecStatMonitorGlobalDrop 35 }

		
		-- 1.3.6.1.4.1.2011.6.122.15.1.2.3.36
		hwSecStatLargeIcmpDropOcts OBJECT-TYPE
			SYNTAX Counter64
			MAX-ACCESS read-only
			STATUS current
			DESCRIPTION
				"The total bytes of packets dropped due to Large Icmp attack."
			::= { hwSecStatMonitorGlobalDrop 36 }

		
		-- 1.3.6.1.4.1.2011.6.122.15.1.2.3.37
		hwSecStatOtherProtocolDropPkts OBJECT-TYPE
			SYNTAX Counter64
			MAX-ACCESS read-only
			STATUS current
			DESCRIPTION
				"The total number of packets dropped dropped by other protocol."
			::= { hwSecStatMonitorGlobalDrop 37 }

		
		-- 1.3.6.1.4.1.2011.6.122.15.1.2.3.38
		hwSecStatOtherProtocolDropOcts OBJECT-TYPE
			SYNTAX Counter64
			MAX-ACCESS read-only
			STATUS current
			DESCRIPTION
				"The total bytes of packets dropped dropped by other protocol."
			::= { hwSecStatMonitorGlobalDrop 38 }

		
		-- 1.3.6.1.4.1.2011.6.122.15.1.2.3.39
		hwSecStatSecurityPolicyDenyPkts OBJECT-TYPE
			SYNTAX Counter64
			MAX-ACCESS read-only
			STATUS current
			DESCRIPTION
				"The total number of packets dropped dropped by security."
			::= { hwSecStatMonitorGlobalDrop 39 }

		
		-- 1.3.6.1.4.1.2011.6.122.15.1.2.3.40
		hwSecStatSecurityPolicyDenyOcts OBJECT-TYPE
			SYNTAX Counter64
			MAX-ACCESS read-only
			STATUS current
			DESCRIPTION
				"The total bytes of packets dropped dropped by security."
			::= { hwSecStatMonitorGlobalDrop 40 }

		
		-- 1.3.6.1.4.1.2011.6.122.15.1.2.3.41
		hwSecStatClearGlobalDropInfo OBJECT-TYPE
			SYNTAX Integer32 (0..1)
			MAX-ACCESS read-write
			STATUS current
			DESCRIPTION
				"
				Use this OID to clear the global dropped packets statistics information.
				When you want to clear the information, set this OID to 1.
				"
			::= { hwSecStatMonitorGlobalDrop 41 }

		
		-- 1.3.6.1.4.1.2011.6.122.15.1.3
		hwSecStatConformance OBJECT IDENTIFIER ::= { hwSecStatGlobal 3 }

		
		-- 1.3.6.1.4.1.2011.6.122.15.1.3.1
		hwSecStatCompliance OBJECT IDENTIFIER ::= { hwSecStatConformance 1 }

		
		-- 1.3.6.1.4.1.2011.6.122.15.1.3.2
		hwSecStatMibGroups OBJECT IDENTIFIER ::= { hwSecStatConformance 2 }

		
		-- 1.3.6.1.4.1.2011.6.122.15.1.3.2.1
		hwSecStatGlobalCfgGroup OBJECT-GROUP
			OBJECTS { hwSecStatTcpPktScale, hwSecStatUdpPktScale, hwSecStatIcmpPktScale, hwSecStatAlteration, hwSecStatCalcTime, 
				hwSecStatTcpSessNumMax, hwSecStatTcpSessNumMin, hwSecStatUdpSessNumMax, hwSecStatGlobalSessSetDefault, hwSecStatPktScaleSetDefault, 
				hwSecStatUdpSessNumMin, hwSecStatGlobalStatEnable }
			STATUS current
			DESCRIPTION 
				"Description."
			::= { hwSecStatMibGroups 1 }

		
		-- 1.3.6.1.4.1.2011.6.122.15.1.3.2.2
		hwSecStatGlobalMonitorGroup OBJECT-GROUP
			OBJECTS { hwSecStatMonTotalSess, hwSecStatMonHalfConn, hwSecStatMonRcvIcmpPkts, hwSecStatMonRcvIcmpOcts, hwSecStatMonRcvTcpPkts, 
				hwSecStatMonRcvTcpOcts, hwSecStatMonRcvUdpPkts, hwSecStatMonRcvUdpOcts, hwSecStatMonRcvEtcPkts, hwSecStatMonRcvEtcOcts, 
				hwSecStatMonPassIcmpPkts, hwSecStatMonPassIcmpOcts, hwSecStatMonPassTcpPkts, hwSecStatMonPassTcpOcts, hwSecStatMonPassUdpPkts, 
				hwSecStatMonPassUdpOcts, hwSecStatMonPassEtcPkts, hwSecStatMonPassEtcOcts, hwSecStatMonSynPkts, hwSecStatMonFinPkts, 
				hwSecStatMonSynAckPkts, hwSecStatMonRstPkts, hwSecStatMonRcvFragPkts, hwSecStatMonRcvFragOcts, hwSecStatMonFtpSessions, 
				hwSecStatMonRcvFtpPkts, hwSecStatMonRcvFtpOcts, hwSecStatMonSmtpSessions, hwSecStatMonRcvSmtpPkts, hwSecStatMonRcvSmtpOcts, 
				hwSecStatMonHttpSessions, hwSecStatMonRcvHttpPkts, hwSecStatMonRcvHttpOcts, hwSecStatMonH323Sessions, hwSecStatMonRcvH323Pkts, 
				hwSecStatMonRcvH323Octs, hwSecStatMonRtspSessions, hwSecStatMonRcvRtspPkts, hwSecStatMonRcvRtspOcts, hwSecStatMonJavaAtckNum, 
				hwSecStatNoSessTblPkts, hwSecStatNoSessTblOcts, hwSecStatSeqErrPkts, hwSecStatSeqErrOcts, hwSecStatIcmpFloodDropPkts, 
				hwSecStatIcmpFloodDropOcts, hwSecStatUdpFloodDropPkts, hwSecStatUdpFloodDropOcts, hwSecStatAlgDropPkts, hwSecStatAlgDropOcts, 
				hwSecStatIPVerErrDropPkts, hwSecStatIpCrcDropPkts, hwSecStatIpTTLDropPkts, hwSecStatMonCurSessSpeed, hwSecStatMonPeakSessSpeed, 
				hwSecStatMonTotalBootConnNum, hwSecStatProtoErrDropPkts, hwSecStatAclDenyNonIcmpPkts, hwSecStatAclDenyNonIcmpOcts, hwSecStatAclDenyIcmpPkts, 
				hwSecStatAclDenyIcmpOcts, hwSecStatBlsDenyPkts, hwSecStatClearGlobalDropInfo, hwSecStatClearGlobalAppInfo, hwSecStatClearGlobalSessFlowInfo, 
				hwSecStatBlsDenyOcts, hwSecStatMonTcpSess, hwSecStatMonUdpSess, hwSecStatMonIcmpSess, hwSecStatMonSvrMapTblNum, 
				hwSecStatFragTblNum, hwSecStatMonAllPkts, hwSecStatMonAllOcts }
			STATUS current
			DESCRIPTION 
				"Description."
			::= { hwSecStatMibGroups 2 }

		
		-- 1.3.6.1.4.1.2011.6.122.15.2
		hwSecStatPerfAndPhyTable OBJECT-TYPE
			SYNTAX SEQUENCE OF HwSecStatPerfAndPhyEntry
			MAX-ACCESS not-accessible
			STATUS current
			DESCRIPTION
				" "
			::= { hwSecStatMibObjects 2 }

		
		-- 1.3.6.1.4.1.2011.6.122.15.2.1
		hwSecStatPerfAndPhyEntry OBJECT-TYPE
			SYNTAX HwSecStatPerfAndPhyEntry
			MAX-ACCESS not-accessible
			STATUS current
			DESCRIPTION
				" "
			INDEX { hwSecStatPerfIndex }
			::= { hwSecStatPerfAndPhyTable 1 }

		
		HwSecStatPerfAndPhyEntry ::=
			SEQUENCE { 
				hwSecStatPerfIndex
					Integer32,
				hwSecStatPerfSlot
					Integer32,
				hwSecStatPerfCPU
					Integer32,
				hwSecStatSessCount
					Gauge32,
				hwSecStatSessSpeed
					Gauge32,
				hwSecStatUsage
					Gauge32,
				hwSecStatTemperature
					Gauge32,
				hwSecStatVoltage
					Gauge32,
				hwSecStatPerfCpuUsage
					OCTET STRING,
				hwSecStatPerfMemUsage
					Gauge32,
				hwSecStatPerfTotalMemUsage
					Gauge32
			 }

		-- 1.3.6.1.4.1.2011.6.122.15.2.1.1
		hwSecStatPerfIndex OBJECT-TYPE
			SYNTAX Integer32
			MAX-ACCESS not-accessible
			STATUS current
			DESCRIPTION
				"The index of hwSecStatPerfAndPhyTable."
			::= { hwSecStatPerfAndPhyEntry 1 }

		
		-- 1.3.6.1.4.1.2011.6.122.15.2.1.2
		hwSecStatPerfSlot OBJECT-TYPE
			SYNTAX Integer32 (1..16)
			MAX-ACCESS read-only
			STATUS current
			DESCRIPTION
				"The slot number."
			::= { hwSecStatPerfAndPhyEntry 2 }

		
		-- 1.3.6.1.4.1.2011.6.122.15.2.1.3
		hwSecStatPerfCPU OBJECT-TYPE
			SYNTAX Integer32 (0..3)
			MAX-ACCESS read-only
			STATUS current
			DESCRIPTION
				"The CPU number."
			::= { hwSecStatPerfAndPhyEntry 3 }

		
		-- 1.3.6.1.4.1.2011.6.122.15.2.1.4
		hwSecStatSessCount OBJECT-TYPE
			SYNTAX Gauge32
			MAX-ACCESS read-only
			STATUS current
			DESCRIPTION
				"The Session count of the CPU."
			::= { hwSecStatPerfAndPhyEntry 4 }

		
		-- 1.3.6.1.4.1.2011.6.122.15.2.1.5
		hwSecStatSessSpeed OBJECT-TYPE
			SYNTAX Gauge32
			MAX-ACCESS read-only
			STATUS current
			DESCRIPTION
				"Session creation rate of CPU."
			::= { hwSecStatPerfAndPhyEntry 5 }

		
		-- 1.3.6.1.4.1.2011.6.122.15.2.1.6
		hwSecStatUsage OBJECT-TYPE
			SYNTAX Gauge32 (0..100)
			MAX-ACCESS read-only
			STATUS current
			DESCRIPTION
				"The average usage of the CPU."
			::= { hwSecStatPerfAndPhyEntry 6 }

		
		-- 1.3.6.1.4.1.2011.6.122.15.2.1.7
		hwSecStatTemperature OBJECT-TYPE
			SYNTAX Gauge32
			MAX-ACCESS read-only
			STATUS current
			DESCRIPTION
				"The temperature of the CPU."
			::= { hwSecStatPerfAndPhyEntry 7 }

		
		-- 1.3.6.1.4.1.2011.6.122.15.2.1.8
		hwSecStatVoltage OBJECT-TYPE
			SYNTAX Gauge32
			MAX-ACCESS read-only
			STATUS current
			DESCRIPTION
				"The Voltage of the CPU."
			::= { hwSecStatPerfAndPhyEntry 8 }

		
		-- 1.3.6.1.4.1.2011.6.122.15.2.1.9
		hwSecStatPerfCpuUsage OBJECT-TYPE
			SYNTAX OCTET STRING (SIZE (0..65535))
			MAX-ACCESS read-only
			STATUS current
			DESCRIPTION
				"The detail usage information of the CPU."
			::= { hwSecStatPerfAndPhyEntry 9 }

		
		-- 1.3.6.1.4.1.2011.6.122.15.2.1.10
		hwSecStatPerfMemUsage OBJECT-TYPE
			SYNTAX Gauge32  (0..100)
			MAX-ACCESS read-only
			STATUS current
			DESCRIPTION
				"The detail usage information of the memory."
			::= { hwSecStatPerfAndPhyEntry 10 }
			
			
		-- 1.3.6.1.4.1.2011.6.122.15.2.1.11
		hwSecStatPerfTotalMemUsage OBJECT-TYPE
			SYNTAX Gauge32 (0..100)
			MAX-ACCESS read-only
			STATUS current
			DESCRIPTION
				"The detail total usage information of the memory."
			::= { hwSecStatPerfAndPhyEntry 11 }

		
		-- 1.3.6.1.4.1.2011.6.122.15.3
		hwSecStatTraps OBJECT IDENTIFIER ::= { hwSecStatMibObjects 3 }

		
		-- 1.3.6.1.4.1.2011.6.122.15.3.1
		hwSecStatObjests OBJECT IDENTIFIER ::= { hwSecStatTraps 1 }

		-- 1.3.6.1.4.1.2011.6.122.15.3.1.1
		hwSecStatTrapBoardType OBJECT-TYPE
			SYNTAX Integer32 (1..3)
			MAX-ACCESS accessible-for-notify
			STATUS current
			DESCRIPTION
				"The board type."
			::= { hwSecStatObjests 1 }

		-- 1.3.6.1.4.1.2011.6.122.15.3.1.2
		hwSecStatTrapSlot OBJECT-TYPE
			SYNTAX Integer32 (1..128)
			MAX-ACCESS accessible-for-notify
			STATUS current
			DESCRIPTION
				"The slot number."
			::= { hwSecStatObjests 2 }

		
		-- 1.3.6.1.4.1.2011.6.122.15.3.1.3
		hwSecStatTrapCPU OBJECT-TYPE
			SYNTAX Integer32 (0..3)
			MAX-ACCESS accessible-for-notify
			STATUS current
			DESCRIPTION
				"The CPU number."
			::= { hwSecStatObjests 3 }

		
		-- 1.3.6.1.4.1.2011.6.122.15.3.1.4
		hwSecStatPerfTrapVcpu OBJECT-TYPE
			SYNTAX Integer32 (0..127)
			MAX-ACCESS accessible-for-notify
			STATUS current
			DESCRIPTION
				"The VCPU number."
			::= { hwSecStatObjests 4 }

		
		-- 1.3.6.1.4.1.2011.6.122.15.3.1.5
		hwSecStatPerfTrapMemType OBJECT-TYPE
			SYNTAX Integer32 (0..3)
			MAX-ACCESS accessible-for-notify
			STATUS current
			DESCRIPTION
				"The memory type."
			::= { hwSecStatObjests 5 }

		
		-- 1.3.6.1.4.1.2011.6.122.15.3.1.6
		hwSecStatSessTrapCount OBJECT-TYPE
			SYNTAX Gauge32 (0..2000000)
			MAX-ACCESS accessible-for-notify
			STATUS current
			DESCRIPTION
				"The Session count of the CPU."
			::= { hwSecStatObjests 6 }

		
		-- 1.3.6.1.4.1.2011.6.122.15.3.1.7
		hwSecStatSessTrapThreshold OBJECT-TYPE
			SYNTAX Integer32 (1..2000000)
			MAX-ACCESS accessible-for-notify
			STATUS current
			DESCRIPTION
				"Alarm threshold of CPU session count."
			::= { hwSecStatObjests 7 }

		
		-- 1.3.6.1.4.1.2011.6.122.15.3.1.8
		hwSecStatSessRateTrapCount OBJECT-TYPE
			SYNTAX Gauge32 (0..2000000)
			MAX-ACCESS accessible-for-notify
			STATUS current
			DESCRIPTION
				"The rate of creating sessions."
			::= { hwSecStatObjests 8 }

		
		-- 1.3.6.1.4.1.2011.6.122.15.3.1.9
		hwSecStatSessRateTrapThreshold OBJECT-TYPE
			SYNTAX Integer32 (1..2000000)
			MAX-ACCESS accessible-for-notify
			STATUS current
			DESCRIPTION
				"Alarm threshold of CPU session creating rate."
			::= { hwSecStatObjests 9 }

		
		-- 1.3.6.1.4.1.2011.6.122.15.3.1.10
		hwSecStatPerfTrapCpuUsage OBJECT-TYPE
			SYNTAX Gauge32 (0..100)
			MAX-ACCESS accessible-for-notify
			STATUS current
			DESCRIPTION
				"The CPU usage."
			::= { hwSecStatObjests 10 }

		
		-- 1.3.6.1.4.1.2011.6.122.15.3.1.11
		hwSecStatPerfTrapCpuThreshold OBJECT-TYPE
			SYNTAX Integer32 (0..100)
			MAX-ACCESS accessible-for-notify
			STATUS current
			DESCRIPTION
				"The CPU usage threshold."
			::= { hwSecStatObjests 11 }

		
		-- 1.3.6.1.4.1.2011.6.122.15.3.1.12
		hwSecStatPerfTrapMemUsage OBJECT-TYPE
			SYNTAX Gauge32 (0..100)
			MAX-ACCESS accessible-for-notify
			STATUS current
			DESCRIPTION
				"The memory usage."
			::= { hwSecStatObjests 12 }

		
		-- 1.3.6.1.4.1.2011.6.122.15.3.1.13
		hwSecStatPerfTrapMemThreshold OBJECT-TYPE
			SYNTAX Integer32 (10..100)
			MAX-ACCESS accessible-for-notify
			STATUS current
			DESCRIPTION
				"The memory usage threshold."
			::= { hwSecStatObjests 13 }

        -- 1.3.6.1.4.1.2011.6.122.15.3.1.14
		hwSecStatPerfTrapCpucarThreshold OBJECT-TYPE
			SYNTAX Integer32 (1..100)
			MAX-ACCESS accessible-for-notify
			STATUS current
			DESCRIPTION
				"The cpu car threshold."
			::= { hwSecStatObjests 14 }

        -- 1.3.6.1.4.1.2011.6.122.15.3.1.15
		hwSecStatPerfPerformanceCurSecond OBJECT-TYPE
			SYNTAX Integer32 
			MAX-ACCESS accessible-for-notify
			STATUS current
			DESCRIPTION
				"The Performance Cur Second of the cpu."
			::= { hwSecStatObjests 15 }
		
		-- 1.3.6.1.4.1.2011.6.122.15.3.1.16
		hwSecStatSvrMapTableCount OBJECT-TYPE
			SYNTAX Gauge32 
			MAX-ACCESS accessible-for-notify
			STATUS current
			DESCRIPTION
				"Number of used server-map entries."
			::= { hwSecStatObjests 16 }			 
			
		-- 1.3.6.1.4.1.2011.6.122.15.3.1.17
		hwSecStatSvrMapTableThreshold OBJECT-TYPE
			SYNTAX Gauge32 
			MAX-ACCESS accessible-for-notify
			STATUS current
			DESCRIPTION
				"Alarm threshold of server-map entries."
			::= { hwSecStatObjests 17 }			
		
		-- 1.3.6.1.4.1.2011.6.122.15.3.1.18
		hwSecStatSvrMap6TableCount OBJECT-TYPE
			SYNTAX Gauge32 
			MAX-ACCESS accessible-for-notify
			STATUS current
			DESCRIPTION
				"Number of used server-map6 entries."
			::= { hwSecStatObjests 18 }			 
			
		-- 1.3.6.1.4.1.2011.6.122.15.3.1.19
		hwSecStatSvrMap6TableThreshold OBJECT-TYPE
			SYNTAX Gauge32 
			MAX-ACCESS accessible-for-notify
			STATUS current
			DESCRIPTION
				"Alarm threshold of server-map6 entries."
			::= { hwSecStatObjests 19 }
		
		-- 1.3.6.1.4.1.2011.6.122.15.3.1.20
		hwSecStatBLSItemCount OBJECT-TYPE
			SYNTAX Gauge32 
			MAX-ACCESS accessible-for-notify
			STATUS current
			DESCRIPTION
				"Number of used dynamic blacklist entries."
			::= { hwSecStatObjests 20 }			 
			
		-- 1.3.6.1.4.1.2011.6.122.15.3.1.21
		hwSecStatBLSItemThreshold OBJECT-TYPE
			SYNTAX Gauge32 
			MAX-ACCESS accessible-for-notify
			STATUS current
			DESCRIPTION
				"Alarm threshold of dynamic blacklist entries."
			::= { hwSecStatObjests 21 } 
		
		-- 1.3.6.1.4.1.2011.6.122.15.3.1.22
		hwSecStatSuddenChangeRatio OBJECT-TYPE
			SYNTAX Gauge32 
			MAX-ACCESS accessible-for-notify
			STATUS current
			DESCRIPTION
				"Ratio of suddenly changed sessions."
			::= { hwSecStatObjests 22 }			 
			
		-- 1.3.6.1.4.1.2011.6.122.15.3.1.23
		hwSecStatSuddenChangeRatioThreshold OBJECT-TYPE
			SYNTAX Gauge32 
			MAX-ACCESS accessible-for-notify
			STATUS current
			DESCRIPTION
				"Threshold of the ratio of suddenly changed sessions."
			::= { hwSecStatObjests 23 }        
		
		-- 1.3.6.1.4.1.2011.6.122.15.3.1.24
		hwSecStatSuddenChangeCurSess OBJECT-TYPE
			SYNTAX Gauge32 
			MAX-ACCESS accessible-for-notify
			STATUS current
			DESCRIPTION
				"Number of suddenly changed sessions in the current period."
			::= { hwSecStatObjests 24 }

		-- 1.3.6.1.4.1.2011.6.122.15.3.1.25
		hwSecStatSuddenChangeLastSess OBJECT-TYPE
			SYNTAX Gauge32 
			MAX-ACCESS accessible-for-notify
			STATUS current
			DESCRIPTION
				"Number of suddenly changed sessions in the last period."
			::= { hwSecStatObjests 25 }
		-- 1.3.6.1.4.1.2011.6.122.15.3.1.26
		hwSecStatCreateLimitCpuUsage OBJECT-TYPE
			SYNTAX Gauge32 
			MAX-ACCESS accessible-for-notify
			STATUS current
			DESCRIPTION
				"Current CPU usage."
			::= { hwSecStatObjests 26 }
		-- 1.3.6.1.4.1.2011.6.122.15.3.1.27
		hwSecStatCreateLimitPassPacketNum OBJECT-TYPE
			SYNTAX Gauge32 
			MAX-ACCESS accessible-for-notify
			STATUS current
			DESCRIPTION
				"Number of passing packets during new session suppression."
			::= { hwSecStatObjests 27 }
		-- 1.3.6.1.4.1.2011.6.122.15.3.1.28
		hwSecStatCreateLimitBlockPacketNum OBJECT-TYPE
			SYNTAX Gauge32 
			MAX-ACCESS accessible-for-notify
			STATUS current
			DESCRIPTION
				"Number of blocked packets during new session suppression."
			::= { hwSecStatObjests 28 }		
		-- 1.3.6.1.4.1.2011.6.122.15.3.1.29
		hwSecStatFragSessCount OBJECT-TYPE
			SYNTAX Gauge32 
			MAX-ACCESS accessible-for-notify
			STATUS current
			DESCRIPTION
				"Number of used frag session entries."
			::= { hwSecStatObjests 29 } 
			
	                   -- 1.3.6.1.4.1.2011.6.122.15.3.1.30
		hwSecStatFragSessThreshold OBJECT-TYPE
			SYNTAX Gauge32 
			MAX-ACCESS accessible-for-notify
			STATUS current
			DESCRIPTION
				"Alarm threshold of dynamic frag session entries."
			::= { hwSecStatObjests 30 }  
		-- 1.3.6.1.4.1.2011.6.122.15.3.1.31
		hwSecStatFrag6SessCount OBJECT-TYPE
			SYNTAX Gauge32 
			MAX-ACCESS accessible-for-notify
			STATUS current
			DESCRIPTION
				"Number of used IPv6 frag session entries."
			::= { hwSecStatObjests 31 } 
			
	                    -- 1.3.6.1.4.1.2011.6.122.15.3.1.32
		hwSecStatFrag6SessThreshold OBJECT-TYPE
			SYNTAX Gauge32 
			MAX-ACCESS accessible-for-notify
			STATUS current
			DESCRIPTION
				"Alarm threshold of dynamic IPv6 frag session entries."
			::= { hwSecStatObjests 32 }  
		
		-- 1.3.6.1.4.1.2011.6.122.15.3.2
		hwSecStatSessTraps OBJECT IDENTIFIER ::= { hwSecStatTraps 2 }

		
		-- 1.3.6.1.4.1.2011.6.122.15.3.2.1
		hwSecStatSessOverThreshold NOTIFICATION-TYPE
			OBJECTS { hwSecStatTrapSlot, hwSecStatTrapCPU, hwSecStatSessTrapCount, hwSecStatSessTrapThreshold }
			STATUS current
			DESCRIPTION 
				"The session count of the CPU exceeds the upper limit of the threshold."
			::= { hwSecStatSessTraps 1 }

		
		-- 1.3.6.1.4.1.2011.6.122.15.3.2.2
		hwSecStatSessBelowThreshold NOTIFICATION-TYPE
			OBJECTS { hwSecStatTrapSlot, hwSecStatTrapCPU, hwSecStatSessTrapCount, hwSecStatSessTrapThreshold }
			STATUS current
			DESCRIPTION 
				"The session count of the CPU restores to be lower than the threshold corresponding to the upper limit of the threshold."
			::= { hwSecStatSessTraps 2 }

		
		-- 1.3.6.1.4.1.2011.6.122.15.3.2.3
		hwSecStatSessRateOverThreshold NOTIFICATION-TYPE
			OBJECTS { hwSecStatTrapSlot, hwSecStatTrapCPU, hwSecStatSessRateTrapCount, hwSecStatSessRateTrapThreshold }
			STATUS current
			DESCRIPTION 
				"The rate of creating sessions exceeds the upper limit of the threshold."
			::= { hwSecStatSessTraps 3 }

		
		-- 1.3.6.1.4.1.2011.6.122.15.3.2.4
		hwSecStatSessRateBelowThreshold NOTIFICATION-TYPE
			OBJECTS { hwSecStatTrapSlot, hwSecStatTrapCPU, hwSecStatSessRateTrapCount, hwSecStatSessRateTrapThreshold }
			STATUS current
			DESCRIPTION 
				"The rate of creating sessions restores to be lower than the threshold corresponding to the upper limit of the threshold."
			::= { hwSecStatSessTraps 4 }


                                           -- 1.3.6.1.4.1.2011.6.122.15.3.2.5
		hwSecStatFastSessOverThreshold NOTIFICATION-TYPE
			OBJECTS { hwSecStatTrapSlot, hwSecStatTrapCPU, hwSecStatSessTrapCount, hwSecStatSessTrapThreshold }
			STATUS current
			DESCRIPTION 
				"The fast-forwarding session count of the LPU exceeds the upper limit of the threshold."
			::= { hwSecStatSessTraps 5 }

		
		-- 1.3.6.1.4.1.2011.6.122.15.3.2.6
		hwSecStatFastSessBelowThreshold NOTIFICATION-TYPE
			OBJECTS { hwSecStatTrapSlot, hwSecStatTrapCPU, hwSecStatSessTrapCount, hwSecStatSessTrapThreshold }
			STATUS current
			DESCRIPTION 
				"The fast-forwarding session count of the LPU restores to be lower than the threshold corresponding to the upper limit of the threshold."
			::= { hwSecStatSessTraps 6 }
		

		-- 1.3.6.1.4.1.2011.6.122.15.3.3
		hwSecStatPerfTraps OBJECT IDENTIFIER ::= { hwSecStatTraps 3 }

		
		-- 1.3.6.1.4.1.2011.6.122.15.3.3.1
		hwSecStatPerfTrapCpuOverThreshold NOTIFICATION-TYPE
			OBJECTS { hwSecStatTrapBoardType, hwSecStatTrapSlot, hwSecStatTrapCPU, hwSecStatPerfTrapVcpu, hwSecStatPerfTrapCpuUsage, hwSecStatPerfTrapCpuThreshold
				 }
			STATUS current
			DESCRIPTION 
				"The usage of cpu exceeds the upper limit of the threshold."
			::= { hwSecStatPerfTraps 1 }

		
		-- 1.3.6.1.4.1.2011.6.122.15.3.3.2
		hwSecStatPerfTrapCpuBelowThreshold NOTIFICATION-TYPE
			OBJECTS { hwSecStatTrapBoardType, hwSecStatTrapSlot, hwSecStatTrapCPU, hwSecStatPerfTrapVcpu, hwSecStatPerfTrapCpuUsage, hwSecStatPerfTrapCpuThreshold
				 }
			STATUS current
			DESCRIPTION 
				"The usage of cpu restores to be lower than the threshold corresponding to the upper limit of the threshold."
			::= { hwSecStatPerfTraps 2 }

		
		-- 1.3.6.1.4.1.2011.6.122.15.3.3.3
		hwSecStatPerfTrapMemOverThreshold NOTIFICATION-TYPE
			OBJECTS { hwSecStatTrapBoardType, hwSecStatTrapSlot, hwSecStatTrapCPU, hwSecStatPerfTrapMemType, hwSecStatPerfTrapMemUsage, hwSecStatPerfTrapMemThreshold
				 }
			STATUS current
			DESCRIPTION 
				"The usage of memory exceeds the upper limit of the threshold."
			::= { hwSecStatPerfTraps 3 }

		
		-- 1.3.6.1.4.1.2011.6.122.15.3.3.4
		hwSecStatPerfTrapMemBelowThreshold NOTIFICATION-TYPE
			OBJECTS { hwSecStatTrapBoardType, hwSecStatTrapSlot, hwSecStatTrapCPU, hwSecStatPerfTrapMemType, hwSecStatPerfTrapMemUsage, hwSecStatPerfTrapMemThreshold
				 }
			STATUS current
			DESCRIPTION 
				"The usage of memory restores to be lower than the threshold corresponding to the upper limit of the threshold."
			::= { hwSecStatPerfTraps 4 }

                      -- 1.3.6.1.4.1.2011.6.122.15.3.3.5
		hwSecStatPerfTrapOverCpuCarThreshold NOTIFICATION-TYPE
			OBJECTS { hwSecStatTrapSlot, hwSecStatTrapCPU, hwSecStatPerfTrapCpucarThreshold, hwSecStatPerfPerformanceCurSecond
				 }
			STATUS current
			DESCRIPTION 
				"The usage of cpu car exceeds the upper limit of the threshold."
			::= { hwSecStatPerfTraps 5 }

		-- 1.3.6.1.4.1.2011.6.122.15.3.4
		hwSecStatDynamicRourceTraps OBJECT IDENTIFIER ::= { hwSecStatTraps 4 }

		-- 1.3.6.1.4.1.2011.6.122.15.3.4.1
		hwSecStatSvrMapTrapOverThreshold NOTIFICATION-TYPE
			OBJECTS { hwSecStatTrapSlot, hwSecStatTrapCPU, hwSecStatSvrMapTableCount, hwSecStatSvrMapTableThreshold
				 }
			STATUS current
			DESCRIPTION 
				"The number of used server-map entries exceeded the threshold."
			::= { hwSecStatDynamicRourceTraps 1 } 
			
        -- 1.3.6.1.4.1.2011.6.122.15.3.4.2
		hwSecStatSvrMapTrapBelowThreshold NOTIFICATION-TYPE
			OBJECTS { hwSecStatTrapSlot, hwSecStatTrapCPU, hwSecStatSvrMapTableCount, hwSecStatSvrMapTableThreshold
				 }
			STATUS current
			DESCRIPTION 
				"the number of used server-map entries fell below the threshold."
			::= { hwSecStatDynamicRourceTraps 2 }  
			
        -- 1.3.6.1.4.1.2011.6.122.15.3.4.3
		hwSecStatSvrMap6TrapOverThreshold NOTIFICATION-TYPE
			OBJECTS { hwSecStatTrapSlot, hwSecStatTrapCPU, hwSecStatSvrMap6TableCount, hwSecStatSvrMap6TableThreshold
				 }
			STATUS current
			DESCRIPTION 
				"The number of used server-map6 entries exceeded the threshold."
			::= { hwSecStatDynamicRourceTraps 3 }
		
		-- 1.3.6.1.4.1.2011.6.122.15.3.4.4
		hwSecStatSvrMap6TrapBelowThreshold NOTIFICATION-TYPE
			OBJECTS { hwSecStatTrapSlot, hwSecStatTrapCPU, hwSecStatSvrMap6TableCount, hwSecStatSvrMap6TableThreshold
				 }
			STATUS current
			DESCRIPTION 
				"The number of used server-map6 entries fell below the threshold."
			::= { hwSecStatDynamicRourceTraps 4 }

        -- 1.3.6.1.4.1.2011.6.122.15.3.4.5
		hwSecStatBLSTrapOverThreshold NOTIFICATION-TYPE
			OBJECTS { hwSecStatTrapSlot, hwSecStatTrapCPU, hwSecStatBLSItemCount, hwSecStatBLSItemThreshold
				 }
			STATUS current
			DESCRIPTION 
				"The number of dynamic blacklist entries exceeded the threshold."
			::= { hwSecStatDynamicRourceTraps 5 }
		
		-- 1.3.6.1.4.1.2011.6.122.15.3.4.6
		hwSecStatBLSTrapBelowThreshold NOTIFICATION-TYPE
			OBJECTS { hwSecStatTrapSlot, hwSecStatTrapCPU, hwSecStatBLSItemCount, hwSecStatBLSItemThreshold
				 }
			STATUS current
			DESCRIPTION 
				"The number of dynamic blacklist entries fell below the threshold."
			::= { hwSecStatDynamicRourceTraps 6 }  
		
		-- 1.3.6.1.4.1.2011.6.122.15.3.4.7
		hwSecStatSuddenChangeTrapOverThreshold NOTIFICATION-TYPE
			OBJECTS { hwSecStatTrapSlot, hwSecStatTrapCPU, hwSecStatSuddenChangeLastSess, hwSecStatSuddenChangeCurSess, hwSecStatSuddenChangeRatio, hwSecStatSuddenChangeRatioThreshold				
 				}
			STATUS current
			DESCRIPTION 
				"The ratio of suddenly changed sessions exceeded the threshold."
			::= { hwSecStatDynamicRourceTraps 7 }
		-- 1.3.6.1.4.1.2011.6.122.15.3.4.8
		hwSecStatSessionCreateLimitTrapOverThreshold NOTIFICATION-TYPE
			OBJECTS { hwSecStatTrapSlot, hwSecStatTrapCPU, hwSecStatCreateLimitCpuUsage
 				}
			STATUS current
			DESCRIPTION 
				"New session suppression is triggered after the value exceeds the threshold."
			::= { hwSecStatDynamicRourceTraps 8 }
		-- 1.3.6.1.4.1.2011.6.122.15.3.4.9
		hwSecStatSessionCreateLimitTrapBelowThreshold NOTIFICATION-TYPE
			OBJECTS { hwSecStatTrapSlot, hwSecStatTrapCPU, hwSecStatCreateLimitCpuUsage, hwSecStatCreateLimitPassPacketNum, hwSecStatCreateLimitBlockPacketNum
 				}
			STATUS current
			DESCRIPTION 
				"New session suppression is canceled after the value falls below the threshold."
			::= { hwSecStatDynamicRourceTraps 9 }
                                       -- 1.3.6.1.4.1.2011.6.122.15.3.4.10
		hwSecStatFragSessOverThreshold NOTIFICATION-TYPE
			OBJECTS { hwSecStatTrapSlot, hwSecStatTrapCPU, hwSecStatFragSessCount, hwSecStatFragSessThreshold
				 }
			STATUS current
			DESCRIPTION 
				"The number of used frag sessions exceeded the threshold."
			::= { hwSecStatDynamicRourceTraps 10 }
		
		-- 1.3.6.1.4.1.2011.6.122.15.3.4.11
		hwSecStatFragSessBelowThreshold NOTIFICATION-TYPE
			OBJECTS { hwSecStatTrapSlot, hwSecStatTrapCPU, hwSecStatFragSessCount, hwSecStatFragSessThreshold
				 }
			STATUS current
			DESCRIPTION 
				"The number of used of frag sessions fell below the threshold."
			::= { hwSecStatDynamicRourceTraps 11 }    
			
 	                    -- 1.3.6.1.4.1.2011.6.122.15.3.4.12
		hwSecStatFrag6SessOverThreshold NOTIFICATION-TYPE
			OBJECTS { hwSecStatTrapSlot, hwSecStatTrapCPU, hwSecStatFrag6SessCount, hwSecStatFrag6SessThreshold
				 }
			STATUS current
			DESCRIPTION 
				"The number of used IPv6 frag sessions exceeded the threshold."
			::= { hwSecStatDynamicRourceTraps 12 }
		
		-- 1.3.6.1.4.1.2011.6.122.15.3.4.13
		hwSecStatFrag6SessBelowThreshold NOTIFICATION-TYPE
			OBJECTS { hwSecStatTrapSlot, hwSecStatTrapCPU, hwSecStatFrag6SessCount, hwSecStatFrag6SessThreshold
				 }
			STATUS current
			DESCRIPTION 
				"The number of used of IPv6 frag sessions fell below the threshold."
			::= { hwSecStatDynamicRourceTraps 13 }  

				
--      AQ4D79760
		-- 1.3.6.1.4.1.2011.6.122.15.4
		hwSecStatAlgObjects OBJECT IDENTIFIER ::= { hwSecStatMibObjects 4 }

		
		-- 1.3.6.1.4.1.2011.6.122.15.4.1
		hwSecStatAlgTable OBJECT-TYPE
			SYNTAX SEQUENCE OF HwSecStatAlgEntry
			MAX-ACCESS not-accessible
			STATUS current
			DESCRIPTION
				"This table contains one row per cpu of SPU."
			::= { hwSecStatAlgObjects 1 }

		
		-- 1.3.6.1.4.1.2011.6.122.15.4.1.1
		hwSecStatAlgEntry OBJECT-TYPE
			SYNTAX HwSecStatAlgEntry
			MAX-ACCESS not-accessible
			STATUS current
			DESCRIPTION
				"Information about the Alg information on the device."
			INDEX { hwSecStatAlgIndex }
			::= { hwSecStatAlgTable 1 }

		
		HwSecStatAlgEntry ::=
			SEQUENCE { 
				hwSecStatAlgIndex
					Gauge32,
				hwSecStatAlgFtpSessCount
					Counter64,
				hwSecStatAlgFtpSessSpeed
					Counter64,
				hwSecStatAlgRtspSessCount
					Counter64,
				hwSecStatAlgRtspSessSpeed
					Counter64,
				hwSecStatAlgDnsSessCount
					Counter64,
				hwSecStatAlgDnsSessSpeed
					Counter64,
				hwSecStatAlgSipSessCount
					Counter64,
				hwSecStatAlgSipSessSpeed
					Counter64,
				hwSecStatAlgH323SessCount
					Counter64,
				hwSecStatAlgH323SessSpeed
					Counter64,
				hwSecStatAlgPptpSessCount
					Counter64,
				hwSecStatAlgPptpSessSpeed
					Counter64,
				hwSecStatAlgMmsSessCount
					Counter64,
				hwSecStatAlgMmsSessSpeed
					Counter64,
				hwSecStatAlgRshSessCount
					Counter64,
				hwSecStatAlgRshSessSpeed
					Counter64,
				hwSecStatAlgSqlnetSessCount
					Counter64,
				hwSecStatAlgSqlnetSessSpeed
					Counter64,
				hwSecStatAlgQqSessCount
					Counter64,
				hwSecStatAlgQqSessSpeed
					Counter64,
				hwSecStatAlgMsnSessCount
					Counter64,
				hwSecStatAlgMsnSessSpeed
					Counter64,
				hwSecStatAlgIlsSessCount
					Counter64,
				hwSecStatAlgIlsSessSpeed
					Counter64,
				hwSecStatAlgMgcpSessCount
					Counter64,
				hwSecStatAlgMgcpSessSpeed
					Counter64,
				hwSecStatAlgSccpSessCount
					Counter64,
				hwSecStatAlgSccpSessSpeed
					Counter64,
				hwSecStatAlgNetbiosSessCount
					Counter64,
				hwSecStatAlgNetbiosSessSpeed
					Counter64
			 }

		-- 1.3.6.1.4.1.2011.6.122.15.4.1.1.1
		hwSecStatAlgIndex OBJECT-TYPE
			SYNTAX Gauge32 (1..16)
			MAX-ACCESS not-accessible
			STATUS current
			DESCRIPTION
				"The index (spu slot number) of hwSecStatAlgTable."
			::= { hwSecStatAlgEntry 1 }

		
		-- 1.3.6.1.4.1.2011.6.122.15.4.1.1.2
		hwSecStatAlgFtpSessCount OBJECT-TYPE
			SYNTAX Counter64
			MAX-ACCESS read-only
			STATUS current
			DESCRIPTION
				"The current number of FTP sessions."
			::= { hwSecStatAlgEntry 2 }

		
		-- 1.3.6.1.4.1.2011.6.122.15.4.1.1.3
		hwSecStatAlgFtpSessSpeed OBJECT-TYPE
			SYNTAX Counter64
			MAX-ACCESS read-only
			STATUS current
			DESCRIPTION
				"The rate of creating FTP session."
			::= { hwSecStatAlgEntry 3 }

		
		-- 1.3.6.1.4.1.2011.6.122.15.4.1.1.4
		hwSecStatAlgRtspSessCount OBJECT-TYPE
			SYNTAX Counter64
			MAX-ACCESS read-only
			STATUS current
			DESCRIPTION
				"The current number of RTSP sessions."
			::= { hwSecStatAlgEntry 4 }

		
		-- 1.3.6.1.4.1.2011.6.122.15.4.1.1.5
		hwSecStatAlgRtspSessSpeed OBJECT-TYPE
			SYNTAX Counter64
			MAX-ACCESS read-only
			STATUS current
			DESCRIPTION
				"The rate of creating RTSP session."
			::= { hwSecStatAlgEntry 5 }

		
		-- 1.3.6.1.4.1.2011.6.122.15.4.1.1.6
		hwSecStatAlgDnsSessCount OBJECT-TYPE
			SYNTAX Counter64
			MAX-ACCESS read-only
			STATUS current
			DESCRIPTION
				"The current number of DNS sessions."
			::= { hwSecStatAlgEntry 6 }

		
		-- 1.3.6.1.4.1.2011.6.122.15.4.1.1.7
		hwSecStatAlgDnsSessSpeed OBJECT-TYPE
			SYNTAX Counter64
			MAX-ACCESS read-only
			STATUS current
			DESCRIPTION
				"The rate of creating DNS session."
			::= { hwSecStatAlgEntry 7 }

		
		-- 1.3.6.1.4.1.2011.6.122.15.4.1.1.8
		hwSecStatAlgSipSessCount OBJECT-TYPE
			SYNTAX Counter64
			MAX-ACCESS read-only
			STATUS current
			DESCRIPTION
				"The current number of SIP sessions."
			::= { hwSecStatAlgEntry 8 }

		
		-- 1.3.6.1.4.1.2011.6.122.15.4.1.1.9
		hwSecStatAlgSipSessSpeed OBJECT-TYPE
			SYNTAX Counter64
			MAX-ACCESS read-only
			STATUS current
			DESCRIPTION
				"The rate of creating SIP session."
			::= { hwSecStatAlgEntry 9 }

		
		-- 1.3.6.1.4.1.2011.6.122.15.4.1.1.10
		hwSecStatAlgH323SessCount OBJECT-TYPE
			SYNTAX Counter64
			MAX-ACCESS read-only
			STATUS current
			DESCRIPTION
				"The current number of H323 sessions."
			::= { hwSecStatAlgEntry 10 }

		
		-- 1.3.6.1.4.1.2011.6.122.15.4.1.1.11
		hwSecStatAlgH323SessSpeed OBJECT-TYPE
			SYNTAX Counter64
			MAX-ACCESS read-only
			STATUS current
			DESCRIPTION
				"The rate of creating H323 session."
			::= { hwSecStatAlgEntry 11 }

		
		-- 1.3.6.1.4.1.2011.6.122.15.4.1.1.12
		hwSecStatAlgPptpSessCount OBJECT-TYPE
			SYNTAX Counter64
			MAX-ACCESS read-only
			STATUS current
			DESCRIPTION
				"The current number of PPTP sessions."
			::= { hwSecStatAlgEntry 12 }

		
		-- 1.3.6.1.4.1.2011.6.122.15.4.1.1.13
		hwSecStatAlgPptpSessSpeed OBJECT-TYPE
			SYNTAX Counter64
			MAX-ACCESS read-only
			STATUS current
			DESCRIPTION
				"The rate of creating PPTP session."
			::= { hwSecStatAlgEntry 13 }

		
		-- 1.3.6.1.4.1.2011.6.122.15.4.1.1.14
		hwSecStatAlgMmsSessCount OBJECT-TYPE
			SYNTAX Counter64
			MAX-ACCESS read-only
			STATUS current
			DESCRIPTION
				"The current number of MMS sessions."
			::= { hwSecStatAlgEntry 14 }

		
		-- 1.3.6.1.4.1.2011.6.122.15.4.1.1.15
		hwSecStatAlgMmsSessSpeed OBJECT-TYPE
			SYNTAX Counter64
			MAX-ACCESS read-only
			STATUS current
			DESCRIPTION
				"The rate of creating MMS session."
			::= { hwSecStatAlgEntry 15 }

		
		-- 1.3.6.1.4.1.2011.6.122.15.4.1.1.16
		hwSecStatAlgRshSessCount OBJECT-TYPE
			SYNTAX Counter64
			MAX-ACCESS read-only
			STATUS current
			DESCRIPTION
				"The current number of RSH sessions."
			::= { hwSecStatAlgEntry 16 }

		
		-- 1.3.6.1.4.1.2011.6.122.15.4.1.1.17
		hwSecStatAlgRshSessSpeed OBJECT-TYPE
			SYNTAX Counter64
			MAX-ACCESS read-only
			STATUS current
			DESCRIPTION
				"The rate of creating RSH session."
			::= { hwSecStatAlgEntry 17 }

		
		-- 1.3.6.1.4.1.2011.6.122.15.4.1.1.18
		hwSecStatAlgSqlnetSessCount OBJECT-TYPE
			SYNTAX Counter64
			MAX-ACCESS read-only
			STATUS current
			DESCRIPTION
				"The current number of SQLNET sessions."
			::= { hwSecStatAlgEntry 18 }

		
		-- 1.3.6.1.4.1.2011.6.122.15.4.1.1.19
		hwSecStatAlgSqlnetSessSpeed OBJECT-TYPE
			SYNTAX Counter64
			MAX-ACCESS read-only
			STATUS current
			DESCRIPTION
				"The rate of creating SQLNET session."
			::= { hwSecStatAlgEntry 19 }

		
		-- 1.3.6.1.4.1.2011.6.122.15.4.1.1.20
		hwSecStatAlgQqSessCount OBJECT-TYPE
			SYNTAX Counter64
			MAX-ACCESS read-only
			STATUS current
			DESCRIPTION
				"The current number of QQ sessions."
			::= { hwSecStatAlgEntry 20 }

		
		-- 1.3.6.1.4.1.2011.6.122.15.4.1.1.21
		hwSecStatAlgQqSessSpeed OBJECT-TYPE
			SYNTAX Counter64
			MAX-ACCESS read-only
			STATUS current
			DESCRIPTION
				"The rate of creating QQ session."
			::= { hwSecStatAlgEntry 21 }

		
		-- 1.3.6.1.4.1.2011.6.122.15.4.1.1.22
		hwSecStatAlgMsnSessCount OBJECT-TYPE
			SYNTAX Counter64
			MAX-ACCESS read-only
			STATUS current
			DESCRIPTION
				"The current number of MSN sessions."
			::= { hwSecStatAlgEntry 22 }

		
		-- 1.3.6.1.4.1.2011.6.122.15.4.1.1.23
		hwSecStatAlgMsnSessSpeed OBJECT-TYPE
			SYNTAX Counter64
			MAX-ACCESS read-only
			STATUS current
			DESCRIPTION
				"The rate of creating MSN session."
			::= { hwSecStatAlgEntry 23 }

		
		-- 1.3.6.1.4.1.2011.6.122.15.4.1.1.24
		hwSecStatAlgIlsSessCount OBJECT-TYPE
			SYNTAX Counter64
			MAX-ACCESS read-only
			STATUS current
			DESCRIPTION
				"The current number of ILS sessions."
			::= { hwSecStatAlgEntry 24 }

		
		-- 1.3.6.1.4.1.2011.6.122.15.4.1.1.25
		hwSecStatAlgIlsSessSpeed OBJECT-TYPE
			SYNTAX Counter64
			MAX-ACCESS read-only
			STATUS current
			DESCRIPTION
				"The rate of creating ILS session."
			::= { hwSecStatAlgEntry 25 }

		-- 1.3.6.1.4.1.2011.6.122.15.4.1.1.26
		hwSecStatAlgMgcpSessCount OBJECT-TYPE
			SYNTAX Counter64
			MAX-ACCESS read-only
			STATUS current
			DESCRIPTION
				"The current number of MGCP sessions."
			::= { hwSecStatAlgEntry 26 }

		
		-- 1.3.6.1.4.1.2011.6.122.15.4.1.1.27
		hwSecStatAlgMgcpSessSpeed OBJECT-TYPE
			SYNTAX Counter64
			MAX-ACCESS read-only
			STATUS current
			DESCRIPTION
				"The rate of creating MGCP session."
			::= { hwSecStatAlgEntry 27 }

		
		-- 1.3.6.1.4.1.2011.6.122.15.4.1.1.28
		hwSecStatAlgSccpSessCount OBJECT-TYPE
			SYNTAX Counter64
			MAX-ACCESS read-only
			STATUS current
			DESCRIPTION
				"The current number of SCCP sessions."
			::= { hwSecStatAlgEntry 28 }

		
		-- 1.3.6.1.4.1.2011.6.122.15.4.1.1.29
		hwSecStatAlgSccpSessSpeed OBJECT-TYPE
			SYNTAX Counter64
			MAX-ACCESS read-only
			STATUS current
			DESCRIPTION
				"The rate of creating SCCP session."
			::= { hwSecStatAlgEntry 29 }

		
		-- 1.3.6.1.4.1.2011.6.122.15.4.1.1.30
		hwSecStatAlgNetbiosSessCount OBJECT-TYPE
			SYNTAX Counter64
			MAX-ACCESS read-only
			STATUS current
			DESCRIPTION
				"The current number of NETBIOS sessions."
			::= { hwSecStatAlgEntry 30 }

		
		-- 1.3.6.1.4.1.2011.6.122.15.4.1.1.31
		hwSecStatAlgNetbiosSessSpeed OBJECT-TYPE
			SYNTAX Counter64
			MAX-ACCESS read-only
			STATUS current
			DESCRIPTION
				"The rate of creating NETBIOS session."
			::= { hwSecStatAlgEntry 31 }

		
--      OR:add by wuhuajia00003626 for 	servermap number by cup
                      -- 1.3.6.1.4.1.2011.6.122.15.5
		hwSecStatMibCfgObjects OBJECT IDENTIFIER ::= { hwSecStatMibObjects 5 }

		
		-- 1.3.6.1.4.1.2011.6.122.15.5.1
		hwSecStatServermapTable OBJECT-TYPE
			SYNTAX SEQUENCE OF HwSecStatServermapEntry
			MAX-ACCESS not-accessible
			STATUS current
			DESCRIPTION
				"This table contains one row per SPU."
			::= { hwSecStatMibCfgObjects 1 }

		
		-- 1.3.6.1.4.1.2011.6.122.15.5.1.1
		hwSecStatServermapEntry OBJECT-TYPE
			SYNTAX HwSecStatServermapEntry
			MAX-ACCESS not-accessible
			STATUS current
			DESCRIPTION
				"Information about the server-map information on the device."
			INDEX { hwSecStatServermapIndex }
			::= { hwSecStatServermapTable 1 }

		
		HwSecStatServermapEntry ::=
			SEQUENCE { 
				hwSecStatServermapIndex
					Gauge32,
				hwSecStatServermapSlot
					Gauge32,
				hwSecStatServermapCpu
					Gauge32,
				hwSecStatServermapCurNum
					Gauge32,
				hwSecStatServermapMaxNum
					Gauge32
			 }

		-- 1.3.6.1.4.1.2011.6.122.15.5.1.1.1
		hwSecStatServermapIndex OBJECT-TYPE
			SYNTAX Gauge32
			MAX-ACCESS not-accessible
			STATUS current
			DESCRIPTION
				"Index (slot number and CPU number) of hwSecStatServermapTable."
			::= { hwSecStatServermapEntry 1 }

		
		-- 1.3.6.1.4.1.2011.6.122.15.5.1.1.2
		hwSecStatServermapSlot OBJECT-TYPE
			SYNTAX Gauge32 (1..16)
			MAX-ACCESS read-only
			STATUS current
			DESCRIPTION
				"Slot number"
			::= { hwSecStatServermapEntry 2 }

		
		-- 1.3.6.1.4.1.2011.6.122.15.5.1.1.3
		hwSecStatServermapCpu OBJECT-TYPE
			SYNTAX Gauge32 (0..3)
			MAX-ACCESS read-only
			STATUS current
			DESCRIPTION
				"CPU number"
			::= { hwSecStatServermapEntry 3 }

		
		-- 1.3.6.1.4.1.2011.6.122.15.5.1.1.4
		hwSecStatServermapCurNum OBJECT-TYPE
			SYNTAX Gauge32
			MAX-ACCESS read-only
			STATUS current
			DESCRIPTION
				"The number of server-map in the system currently."
			::= { hwSecStatServermapEntry 4 }

		
		-- 1.3.6.1.4.1.2011.6.122.15.5.1.1.5
		hwSecStatServermapMaxNum OBJECT-TYPE
			SYNTAX Gauge32
			MAX-ACCESS read-only
			STATUS current
			DESCRIPTION
				"The total number of server-map in the system."
			::= { hwSecStatServermapEntry 5 }
		
--  1.3.6.1.4.1.2011.6.122.15.5.3
		-- 1.3.6.1.4.1.2011.6.122.15.5.3
		hwSecStatServiceQualityTable OBJECT-TYPE
			SYNTAX SEQUENCE OF HwSecStatServiceQualityEntry
			MAX-ACCESS not-accessible
			STATUS current
			DESCRIPTION
				"Information about the service quality information on the device."
			::= { hwSecStatMibCfgObjects 3 }
		
		-- 1.3.6.1.4.1.2011.6.122.15.5.3.1
		hwSecStatServiceQualityEntry OBJECT-TYPE
			SYNTAX HwSecStatServiceQualityEntry
			MAX-ACCESS not-accessible
			STATUS current
			DESCRIPTION
				"Information about the service quality information on the device."
			INDEX { hwSecStatServiceQualityIndex }
			::= { hwSecStatServiceQualityTable 1 }
		
		HwSecStatServiceQualityEntry ::=
			SEQUENCE { 
				hwSecStatServiceQualityIndex
					Gauge32,
				hwSecStatServiceQualityProtocol
					OCTET STRING,
				hwSecStatServiceQualityTime
					OCTET STRING,
				hwSecStatServiceQualityRcvPkt
					Counter64,
				hwSecStatServiceQualityDropPkt
					Counter64,
				hwSecStatServiceQualityDropRate
					OCTET STRING,
				hwSecStatServiceQualityConnectRequset
					Counter64,
				hwSecStatServiceQualityConnectSucc
					Counter64,
				hwSecStatServiceQualitySuccessRate
					OCTET STRING,
				hwSecStatServiceQualityDropFibMiss
					Counter64,
				hwSecStatServiceQualityDropArpMiss
					Counter64,
				hwSecStatServiceQualityDropSessExhaust
					Counter64,
				hwSecStatServiceQualityDropPortConflict
					Counter64,
				hwSecStatServiceQualityDropPortExhaust
					Counter64,
				hwSecStatServiceQualityDropAddrExhaust
					Counter64
			 }

		-- 1.3.6.1.4.1.2011.6.122.15.5.3.1.1
		hwSecStatServiceQualityIndex OBJECT-TYPE
			SYNTAX Gauge32
			MAX-ACCESS not-accessible
			STATUS current
			DESCRIPTION
				"Index of the hwSecStatServiceQualityTable."
			::= { hwSecStatServiceQualityEntry 1 }
		
		-- 1.3.6.1.4.1.2011.6.122.15.5.3.1.2
		hwSecStatServiceQualityProtocol OBJECT-TYPE
			SYNTAX OCTET STRING
			MAX-ACCESS read-only
			STATUS current
			DESCRIPTION
				"Protocol."
			::= { hwSecStatServiceQualityEntry 2 }
		
		-- 1.3.6.1.4.1.2011.6.122.15.5.3.1.3
		hwSecStatServiceQualityTime OBJECT-TYPE
			SYNTAX OCTET STRING
			MAX-ACCESS read-only
			STATUS current
			DESCRIPTION
				"Statistical time."
			::= { hwSecStatServiceQualityEntry 3 }
		
		-- 1.3.6.1.4.1.2011.6.122.15.5.3.1.4
		hwSecStatServiceQualityRcvPkt OBJECT-TYPE
			SYNTAX Counter64
			MAX-ACCESS read-only
			STATUS current
			DESCRIPTION
				"Received packet number."
			::= { hwSecStatServiceQualityEntry 4 }
		
		-- 1.3.6.1.4.1.2011.6.122.15.5.3.1.5
		hwSecStatServiceQualityDropPkt OBJECT-TYPE
			SYNTAX Counter64
			MAX-ACCESS read-only
			STATUS current
			DESCRIPTION
				"Dropped packet number."
			::= { hwSecStatServiceQualityEntry 5 }
		
		-- 1.3.6.1.4.1.2011.6.122.15.5.3.1.6
		hwSecStatServiceQualityDropRate OBJECT-TYPE
			SYNTAX OCTET STRING
			MAX-ACCESS read-only
			STATUS current
			DESCRIPTION
				"The drop-rate of the device."
			::= { hwSecStatServiceQualityEntry 6 }
		
		-- 1.3.6.1.4.1.2011.6.122.15.5.3.1.7
		hwSecStatServiceQualityConnectRequset OBJECT-TYPE
			SYNTAX Counter64
			MAX-ACCESS read-only
			STATUS current
			DESCRIPTION
				"The number of connect requset."
			::= { hwSecStatServiceQualityEntry 7 }
		
		-- 1.3.6.1.4.1.2011.6.122.15.5.3.1.8
		hwSecStatServiceQualityConnectSucc OBJECT-TYPE
			SYNTAX Counter64
			MAX-ACCESS read-only
			STATUS current
			DESCRIPTION
				"The number of connect success."
			::= { hwSecStatServiceQualityEntry 8 }
		
		-- 1.3.6.1.4.1.2011.6.122.15.5.3.1.9
		hwSecStatServiceQualitySuccessRate OBJECT-TYPE
			SYNTAX OCTET STRING
			MAX-ACCESS read-only
			STATUS current
			DESCRIPTION
				"The success rate of connect requset."
			::= { hwSecStatServiceQualityEntry 9 }
		
		-- 1.3.6.1.4.1.2011.6.122.15.5.3.1.10
		hwSecStatServiceQualityDropFibMiss OBJECT-TYPE
			SYNTAX Counter64
			MAX-ACCESS read-only
			STATUS current
			DESCRIPTION
				"The total number of packets dropped for fib miss."
			::= { hwSecStatServiceQualityEntry 10 }
		
		-- 1.3.6.1.4.1.2011.6.122.15.5.3.1.11
		hwSecStatServiceQualityDropArpMiss OBJECT-TYPE
			SYNTAX Counter64
			MAX-ACCESS read-only
			STATUS current
			DESCRIPTION
				"The total number of packets dropped for arp miss."
			::= { hwSecStatServiceQualityEntry 11 }
		
		-- 1.3.6.1.4.1.2011.6.122.15.5.3.1.12
		hwSecStatServiceQualityDropSessExhaust OBJECT-TYPE
			SYNTAX Counter64
			MAX-ACCESS read-only
			STATUS current
			DESCRIPTION
				"The total number of packets dropped for session exhaust."
			::= { hwSecStatServiceQualityEntry 12 }
		
		-- 1.3.6.1.4.1.2011.6.122.15.5.3.1.13
		hwSecStatServiceQualityDropPortConflict OBJECT-TYPE
			SYNTAX Counter64
			MAX-ACCESS read-only
			STATUS current
			DESCRIPTION
				"The total number of packets dropped for port conflict."
			::= { hwSecStatServiceQualityEntry 13 }
		
		-- 1.3.6.1.4.1.2011.6.122.15.5.3.1.14
		hwSecStatServiceQualityDropPortExhaust OBJECT-TYPE
			SYNTAX Counter64
			MAX-ACCESS read-only
			STATUS current
			DESCRIPTION
				"The total number of packets dropped for port exhaust."
			::= { hwSecStatServiceQualityEntry 14 }
		
		-- 1.3.6.1.4.1.2011.6.122.15.5.3.1.15
		hwSecStatServiceQualityDropAddrExhaust OBJECT-TYPE
			SYNTAX Counter64
			MAX-ACCESS read-only
			STATUS current
			DESCRIPTION
				"The total number of packets dropped for no-pat address exhaust."
			::= { hwSecStatServiceQualityEntry 15 }
		
		-- 1.3.6.1.4.1.2011.6.122.15.6
		hwSecStatDevice OBJECT IDENTIFIER ::= { hwSecStatMibObjects 6 }		
		
		-- 1.3.6.1.4.1.2011.6.122.15.6.1
		hwSecStatStartupTime OBJECT-TYPE 
			SYNTAX OCTET STRING (SIZE (0..128))
			MAX-ACCESS read-only
			STATUS current
			DESCRIPTION
				"The startup time of the device."
			::= { hwSecStatDevice 1 }
			
		-- 1.3.6.1.4.1.2011.6.122.15.6.2
		hwSecStatDeviceSessCount OBJECT-TYPE
			SYNTAX Gauge32
			MAX-ACCESS read-only
			STATUS current
			DESCRIPTION
				"The session count of the device."
			::= { hwSecStatDevice 2 }
			
		-- 1.3.6.1.4.1.2011.6.122.15.6.3
		hwSecStatDeviceSessSpeed OBJECT-TYPE
			SYNTAX Gauge32
			MAX-ACCESS read-only
			STATUS current
			DESCRIPTION
				"Session creation ration of the device."
			::= { hwSecStatDevice 3 }
			
		-- 1.3.6.1.4.1.2011.6.122.15.6.4
		hwSecStatDeviceThroughput OBJECT-TYPE
			SYNTAX Gauge32
			MAX-ACCESS read-only
			STATUS current
			DESCRIPTION
				"The throughput of the device."
			::= { hwSecStatDevice 4 }

              -- 1.3.6.1.4.1.2011.6.122.15.6.5
		hwSecStatDeviceThroughput64 OBJECT-TYPE
			SYNTAX Counter64
			MAX-ACCESS read-only
			STATUS current
			DESCRIPTION
				"The throughput64 of the device."
			::= { hwSecStatDevice 5}
	        -- 1.3.6.1.4.1.2011.6.122.15.6.6
		hwSecStatDeviceLoggedPackets OBJECT-TYPE
			SYNTAX Counter64
			MAX-ACCESS read-only
			STATUS current
			DESCRIPTION
				"The items of the session log send to device."
			::= { hwSecStatDevice 6}
--      OR:add by lvliang 00272204 for V5R1C00 for forward framework.
		-- 1.3.6.1.4.1.2011.6.122.15.7
		hwSecStatFwdFramework OBJECT IDENTIFIER ::= { hwSecStatMibObjects 7 }
		
		-- 1.3.6.1.4.1.2011.6.122.15.7.1
		hwSecStatFragFlow OBJECT-TYPE 
			SYNTAX Gauge32
			MAX-ACCESS read-only
			STATUS current
			DESCRIPTION
				"The number of fragmented packets."
			::= { hwSecStatFwdFramework 1 }

		-- 1.3.6.1.4.1.2011.6.122.15.7.2
		hwSecStatFragRate OBJECT-TYPE
			SYNTAX Integer32 (0..100)
			MAX-ACCESS read-only
			STATUS current
			DESCRIPTION
				"The fragmented rate of the device."
			::= { hwSecStatFwdFramework 2 }          
			
		-- 1.3.6.1.4.1.2011.6.122.15.8    
		hwSecStatPktRateObjects OBJECT IDENTIFIER ::= { hwSecStatMibObjects 8 }
		
		-- 1.3.6.1.4.1.2011.6.122.15.8.1 		
		hwSecStatSecPolicyRateTable OBJECT-TYPE
			SYNTAX SEQUENCE OF HwSecStatSecPolicyRateEntry
			MAX-ACCESS not-accessible
			STATUS current
			DESCRIPTION
				"This table display bytes and packets of packet matching security policies."		
			::= { hwSecStatPktRateObjects 1 }       
			
		-- 1.3.6.1.4.1.2011.6.122.15.8.1.1 		
		hwSecStatSecPolicyRateEntry OBJECT-TYPE  
			SYNTAX HwSecStatSecPolicyRateEntry
			MAX-ACCESS not-accessible
			STATUS current
			DESCRIPTION
				"Information about bytes and packets of packet matching security policies."		
			INDEX { hwSecStatSecHittedVsysName,
					hwSecStatSecHittedRuleName }
			::= { hwSecStatSecPolicyRateTable 1 }   			
	               
		HwSecStatSecPolicyRateEntry ::=
			SEQUENCE { 
				hwSecStatSecHittedVsysName
					OCTET STRING,
				hwSecStatSecHittedRuleName
					OCTET STRING,
				hwSecStatSecHittedInPackets
					Counter64,
				hwSecStatSecHittedInBytes
					Counter64,
				hwSecStatSecHittedOutPackets
					Counter64,
				hwSecStatSecHittedOutBytes
					Counter64
			 }
	               
	               
		-- 1.3.6.1.4.1.2011.6.122.15.8.1.1.1 		
		hwSecStatSecHittedVsysName OBJECT-TYPE
			SYNTAX OCTET STRING
			MAX-ACCESS read-only
			STATUS current
			DESCRIPTION
				"Virtual system name."
			::= { hwSecStatSecPolicyRateEntry 1 }  
						
		-- 1.3.6.1.4.1.2011.6.122.15.8.1.1.2 		
		hwSecStatSecHittedRuleName OBJECT-TYPE
			SYNTAX OCTET STRING
			MAX-ACCESS read-only
			STATUS current
			DESCRIPTION
				"Rule name of security policy."
			::= { hwSecStatSecPolicyRateEntry 2 }	 
			
		-- 1.3.6.1.4.1.2011.6.122.15.8.1.1.3 		
		hwSecStatSecHittedInPackets OBJECT-TYPE
			SYNTAX Counter64
			MAX-ACCESS read-only
			STATUS current
			DESCRIPTION
				"The value of upstream packets matching a security policy."
			::= { hwSecStatSecPolicyRateEntry 3 }   
			
		-- 1.3.6.1.4.1.2011.6.122.15.8.1.1.4 		
		hwSecStatSecHittedInBytes OBJECT-TYPE
			SYNTAX Counter64
			MAX-ACCESS read-only
			STATUS current
			DESCRIPTION
				"The value of upstream bytes matching a security policy."
			::= { hwSecStatSecPolicyRateEntry 4 }

		-- 1.3.6.1.4.1.2011.6.122.15.8.1.1.5 		
		hwSecStatSecHittedOutPackets OBJECT-TYPE
			SYNTAX Counter64
			MAX-ACCESS read-only
			STATUS current
			DESCRIPTION
				"The value of downstream packets matching a security policy."
			::= { hwSecStatSecPolicyRateEntry 5 }   
			
		-- 1.3.6.1.4.1.2011.6.122.15.8.1.1.6 		
		hwSecStatSecHittedOutBytes OBJECT-TYPE
			SYNTAX Counter64
			MAX-ACCESS read-only
			STATUS current
			DESCRIPTION
				"The value of downstream bytes matching a security policy."
			::= { hwSecStatSecPolicyRateEntry 6 }
								
	END

--
-- HUAWEI-SECURITY-STAT-MIB.mib
--
