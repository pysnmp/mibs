--
-- RS-XX9-DTMB-MIB.mi2
-- MIB generated by MG-SOFT Visual MIB Builder 2010 Version 8.0  Build 403
-- Monday, July 06, 2015 at 12:00:58
--

-- *****************************************************************************
-- *****************************************************************************
-- **
-- **  COPYRIGHT      (c) 2013 Rohde & Schwarz GmbH & Co. KG
-- **                          Muehldorfstrasse 15
-- **    R & S                 D-81671 Muenchen
-- **
-- *****************************************************************************
-- **
-- **  MODULE         RS-XX9-DTMB-MIB
-- **  
-- *****************************************************************************
-- *****************************************************************************

    RS-XX9-DTMB-MIB DEFINITIONS ::= BEGIN
 
        IMPORTS
            commonNotificationAlarmClass            
                FROM RS-XX9-COMMON-MIB            
            rsXx9Dtmb, rsXx9MibModule            
                FROM RS-XX9-SMI-MIB            
            IndexTransmitter, IndexAB, SwitchOnOff, NotificationMask, NotificationPriority, 
            NotificationState            
                FROM RS-XX9-TC-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI            
            TEXTUAL-CONVENTION            
                FROM SNMPv2-TC;
    
    
        rsXx9DtmbMibModule MODULE-IDENTITY 
            LAST-UPDATED "201506231100Z"		-- June 23, 2015 at 11:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines DTMB specific objects
                of XX9000 transmitting systems from Rohde & Schwarz.
                
                The following MIBs are related to this:
                - RS-COMMON-MIB         - mandatory for this MIB
                - RS-XX9-SMI-MIB        - mandatory for this MIB
                - RS-XX9-TC-MIB         - mandatory for this MIB
                - RS-XX9-COMMON-MIB     - mandatory for this MIB"
            REVISION "201507061200Z"		-- July 06, 2015 at 12:00 GMT
            DESCRIPTION 
                "fixed range of dtmbModulationTimeInterleaver
                change labels of DtmbCodeRate
                added dtmbStateTable, dtmbLocalizationTable, dtmbOutModulationTable
                added dtmbTest 
                "
            REVISION "201502271500Z"		-- February 27, 2015 at 15:00 GMT
            DESCRIPTION 
                "updated description texts"
            REVISION "201412221600Z"		-- December 22, 2014 at 16:00 GMT
            DESCRIPTION 
                "updated description texts
                "
            REVISION "201401301100Z"		-- January 30, 2014 at 11:00 GMT
            DESCRIPTION 
                "obsoleted dtmbModulationControlFrame
                update description texts"
            REVISION "201309021100Z"		-- September 02, 2013 at 11:00 GMT
            DESCRIPTION 
                "updated revision with the following changes:
                - added DTMB traps (dtmbEncoderSummary, dtmbManualConfiguration, dtmbActiveConfiguration)
                - added dtmbStatusNotificationTable, containing current trap values
                - added configuration parameters: InfoPacketReplacement, NetworkMode
                - added dtmbTestCarrierPower
                - fixed dtmbTestMode and dtmbConfigurationTpsSource"
            REVISION "201305291500Z"		-- May 29, 2013 at 15:00 GMT
            DESCRIPTION 
                "Preliminary release."
            ::= { rsXx9MibModule 12 }

        
    
--
-- Textual conventions
--
    
        DtmbChannelBandwidth ::= TEXTUAL-CONVENTION
            STATUS current
            DESCRIPTION 
                "mhz6(5)   -  6 MHz
                mhz7(6)   -  7 MHz
                mhz8(7)   -  8 MHz"
            SYNTAX INTEGER
                {
                mhz6(5),
                mhz7(6),
                mhz8(7)
                }

        DtmbGuardInterval ::= TEXTUAL-CONVENTION
            STATUS current
            DESCRIPTION 
                "Description."
            SYNTAX INTEGER
                {
                undefined(1),
                pn420(9),
                pn595(10),
                pn945(11)
                }

        DtmbModulation ::= TEXTUAL-CONVENTION
            STATUS current
            DESCRIPTION 
                "Description."
            SYNTAX INTEGER
                {
                qam16(5),
                qam64(6),
                qam32(7),
                qam4(8),
                qam4nr(9)
                }

        DtmbCodeRate ::= TEXTUAL-CONVENTION
            STATUS current
            DESCRIPTION 
                "Description."
            SYNTAX INTEGER
                {
                undefined(1),
                fourTenth(9),
                sixTenth(10),
                eightTenth(11)
                }

    
--
-- Node definitions
--
    
        rsXx9DtmbNotifications OBJECT IDENTIFIER ::= { rsXx9Dtmb 0 }

        
        dtmbEncoderSummary NOTIFICATION-TYPE
            OBJECTS { commonNotificationAlarmClass, dtmbStatusNotificationPriority, dtmbStatusNotificationState }
            STATUS current
            DESCRIPTION 
                "Encoder summary state.
                
                Possible values:
                off(2)
                fault(3)
                warning(4)
                ok(5)
                
                Notification class: fault"
            ::= { rsXx9DtmbNotifications 1 }

        
        dtmbManualConfiguration NOTIFICATION-TYPE
            OBJECTS { commonNotificationAlarmClass, dtmbStatusNotificationPriority, dtmbStatusNotificationState }
            STATUS current
            DESCRIPTION 
                "Indicates whether the configured DTMB configuration
                is consistent and valid over all three layers.
                If an error is displayed, check whether the sum of all
                segments over the three layers is exactly 13.
                
                Possible values:
                off(2)     - 
                warning(4) - not valid
                ok(5)      - valid
                
                Notification class: warning
                "
            ::= { rsXx9DtmbNotifications 2 }

        
        dtmbActiveConfiguration NOTIFICATION-TYPE
            OBJECTS { commonNotificationAlarmClass, dtmbStatusNotificationPriority, dtmbStatusNotificationState }
            STATUS current
            DESCRIPTION 
                "Indicates whether the active DTMB configuration
                is consistent and valid over all three layers.
                If an error is displayed, check whether the sum of all
                segments over the three layers is exactly 13.
                
                Possible values:
                off(2)     - 
                warning(4) - not valid
                ok(5)      - valid
                
                Notification class: warning
                "
            ::= { rsXx9DtmbNotifications 3 }

        
        dtmbTest NOTIFICATION-TYPE
            OBJECTS { commonNotificationAlarmClass, dtmbStatusNotificationPriority, dtmbStatusNotificationState }
            STATUS current
            DESCRIPTION 
                "One of the test signals is activated. 
                If a test signal is activated, decoding 
                of the transmitted signal by the 
                transmitter will not be possible.
                
                Possible values:
                off(2)     - no test signal generation
                warning(4) - test signal generation is activated
                
                Notification class: warning
                "
            ::= { rsXx9DtmbNotifications 4 }

        
        rsXx9DtmbObjects OBJECT IDENTIFIER ::= { rsXx9Dtmb 1 }

        
        dtmbStatus OBJECT IDENTIFIER ::= { rsXx9DtmbObjects 1 }

        
        dtmbStatusNotificationTable OBJECT-TYPE
            SYNTAX SEQUENCE OF DtmbStatusNotificationEntry
            MAX-ACCESS not-accessible
            STATUS current
            DESCRIPTION
                "The context information/configuration for the DTMB status notifications."
            ::= { dtmbStatus 1 }

        
        dtmbStatusNotificationEntry OBJECT-TYPE
            SYNTAX DtmbStatusNotificationEntry
            MAX-ACCESS not-accessible
            STATUS current
            DESCRIPTION
                "An entry in the dtmbStatusNotificationTable."
            INDEX { dtmbStatusNotificationTxIdx, dtmbStatusNotificationExcIdx, dtmbStatusNotificationIdx }
            ::= { dtmbStatusNotificationTable 1 }

        
        DtmbStatusNotificationEntry ::=
            SEQUENCE { 
                dtmbStatusNotificationTxIdx
                    IndexTransmitter,
                dtmbStatusNotificationExcIdx
                    IndexAB,
                dtmbStatusNotificationIdx
                    Unsigned32,
                dtmbStatusNotificationName
                    INTEGER,
                dtmbStatusNotificationMask
                    NotificationMask,
                dtmbStatusNotificationPriority
                    NotificationPriority,
                dtmbStatusNotificationState
                    NotificationState
             }

        dtmbStatusNotificationTxIdx OBJECT-TYPE
            SYNTAX IndexTransmitter
            MAX-ACCESS not-accessible
            STATUS current
            DESCRIPTION
                "The transmitter index."
            ::= { dtmbStatusNotificationEntry 1 }

        
        dtmbStatusNotificationExcIdx OBJECT-TYPE
            SYNTAX IndexAB
            MAX-ACCESS not-accessible
            STATUS current
            DESCRIPTION
                "This index distinguishes the exciters.
                Necessary if you have dual drive transmitters. "
            ::= { dtmbStatusNotificationEntry 2 }

        
        dtmbStatusNotificationIdx OBJECT-TYPE
            SYNTAX Unsigned32 (1..3)
            MAX-ACCESS not-accessible
            STATUS current
            DESCRIPTION
                "The notification number as below rsXx9DtmbNotifications.
                This is a helper column and therefore not accessible."
            ::= { dtmbStatusNotificationEntry 3 }

        
        dtmbStatusNotificationName OBJECT-TYPE
            SYNTAX INTEGER
                {
                dtmbEncoderSummary(1),
                dtmbManualConfiguration(2),
                dtmbActiveConfiguration(3),
                dtmbTest(4)
                }
            MAX-ACCESS read-write
            STATUS current
            DESCRIPTION
                "The notification number as an enumeration.
                The enumeration correlates with the notifications under rsXx9DtmbNotifications."
            ::= { dtmbStatusNotificationEntry 4 }

        
        dtmbStatusNotificationMask OBJECT-TYPE
            SYNTAX NotificationMask
            MAX-ACCESS read-write
            STATUS current
            DESCRIPTION
                "See TextualConvention for details."
            ::= { dtmbStatusNotificationEntry 5 }

        
        dtmbStatusNotificationPriority OBJECT-TYPE
            SYNTAX NotificationPriority
            MAX-ACCESS read-write
            STATUS current
            DESCRIPTION
                "See TextualConvention for details."
            ::= { dtmbStatusNotificationEntry 6 }

        
        dtmbStatusNotificationState OBJECT-TYPE
            SYNTAX NotificationState
            MAX-ACCESS read-only
            STATUS current
            DESCRIPTION
                "See TextualConvention for details."
            ::= { dtmbStatusNotificationEntry 7 }

        
        dtmbStateTable OBJECT-TYPE
            SYNTAX SEQUENCE OF DtmbStateEntry
            MAX-ACCESS not-accessible
            STATUS current
            DESCRIPTION
                "DTMB state values."
            ::= { dtmbStatus 2 }

        
        dtmbStateEntry OBJECT-TYPE
            SYNTAX DtmbStateEntry
            MAX-ACCESS not-accessible
            STATUS current
            DESCRIPTION
                "An entry in the dtmbStateTable."
            INDEX { dtmbStatusNotificationTxIdx, dtmbStatusNotificationExcIdx }
            ::= { dtmbStateTable 1 }

        
        DtmbStateEntry ::=
            SEQUENCE { 
                dtmbStTxDelayOffset
                    Integer32
             }

        dtmbStTxDelayOffset OBJECT-TYPE
            SYNTAX Integer32
            UNITS "1/10 micro second"
            MAX-ACCESS read-only
            STATUS current
            DESCRIPTION
                "Transmitting time shift compared to other
                transmitters in the DTMB network.
                "
            ::= { dtmbStateEntry 1 }

        
        dtmbSetup OBJECT IDENTIFIER ::= { rsXx9DtmbObjects 2 }

        
        dtmbConfigurationTable OBJECT-TYPE
            SYNTAX SEQUENCE OF DtmbConfigurationEntry
            MAX-ACCESS not-accessible
            STATUS current
            DESCRIPTION
                "General DTMB configuration."
            ::= { dtmbSetup 1 }

        
        dtmbConfigurationEntry OBJECT-TYPE
            SYNTAX DtmbConfigurationEntry
            MAX-ACCESS not-accessible
            STATUS current
            DESCRIPTION
                "An entry in the dtmbConfigurationTable."
            INDEX { dtmbConfigurationTxIdx, dtmbConfigurationExcIdx }
            ::= { dtmbConfigurationTable 1 }

        
        DtmbConfigurationEntry ::=
            SEQUENCE { 
                dtmbConfigurationTxIdx
                    IndexTransmitter,
                dtmbConfigurationExcIdx
                    IndexAB,
                dtmbConfigurationTpsSource
                    INTEGER,
                dtmbConfigurationInfoPacketReplacement
                    INTEGER,
                dtmbConfigurationNetworkMode
                    INTEGER
             }

        dtmbConfigurationTxIdx OBJECT-TYPE
            SYNTAX IndexTransmitter
            MAX-ACCESS not-accessible
            STATUS current
            DESCRIPTION
                "The transmitter index."
            ::= { dtmbConfigurationEntry 1 }

        
        dtmbConfigurationExcIdx OBJECT-TYPE
            SYNTAX IndexAB
            MAX-ACCESS not-accessible
            STATUS current
            DESCRIPTION
                "This index distinguishes the exiters.
                Necessary if you have dual drive transmitters."
            ::= { dtmbConfigurationEntry 2 }

        
        dtmbConfigurationTpsSource OBJECT-TYPE
            SYNTAX INTEGER
                {
                off(1),
                mip(2),
                manual(3),
                sip(4)
                }
            MAX-ACCESS read-write
            STATUS current
            DESCRIPTION
                "Source set for the TPS parameters (TPS = transmission parameter signaling).
                off(1) is an undefined setting and shall not be used.
                The following are possible sources: 
                - MIP (megaframe initialization packet), 
                - SIP (second frame initialization packet)
                - manually selected default settings."
            ::= { dtmbConfigurationEntry 3 }

        
        dtmbConfigurationInfoPacketReplacement OBJECT-TYPE
            SYNTAX INTEGER
                {
                undefined(1),
                off(2),
                on(3)
                }
            MAX-ACCESS read-write
            STATUS current
            DESCRIPTION
                "Controls, whether the information packets (MIP or SIP) shall 
                be contained in the outgiung datastream (off-2), or
                replaced by null-packets (on-3). 
                "
            ::= { dtmbConfigurationEntry 4 }

        
        dtmbConfigurationNetworkMode OBJECT-TYPE
            SYNTAX INTEGER
                {
                undefined(1),
                mfn(2),
                sfnMip(3),
                sfnSip(4)
                }
            MAX-ACCESS read-write
            STATUS current
            DESCRIPTION
                "Used to activate time synchronization. 
                
                MFN: The time of transmission is not controlled. 
                
                SFN (MIP): The time of transmission of a symbol 
                is the same for all the transmitters of a 
                single-frequency network (SFN). The time of 
                transmission signaled by the Megaframe 
                Information Packet is used. 
                
                SFN (SIP):  The time of transmission of a symbol 
                is the same for all the transmitters of a 
                single-frequency network (SFN). The time of 
                transmission signaled by the Session Initiation 
                Protocol is used.
                "
            ::= { dtmbConfigurationEntry 5 }

        
        dtmbModulationTable OBJECT-TYPE
            SYNTAX SEQUENCE OF DtmbModulationEntry
            MAX-ACCESS not-accessible
            STATUS current
            DESCRIPTION
                "DTMB modulation parameters."
            ::= { dtmbSetup 3 }

        
        dtmbModulationEntry OBJECT-TYPE
            SYNTAX DtmbModulationEntry
            MAX-ACCESS not-accessible
            STATUS current
            DESCRIPTION
                "An entry in the dtmbModulationTable."
            AUGMENTS { dtmbConfigurationEntry }
            ::= { dtmbModulationTable 1 }

        
        DtmbModulationEntry ::=
            SEQUENCE { 
                dtmbModulationChannelBandwidth
                    DtmbChannelBandwidth,
                dtmbModulationGuardInterval
                    DtmbGuardInterval,
                dtmbModulationConstellation
                    DtmbModulation,
                dtmbModulationCodeRate
                    DtmbCodeRate,
                dtmbModulationTimeInterleaver
                    INTEGER,
                dtmbModulationControlFrame
                    SwitchOnOff,
                dtmbModulationCarrierMode
                    INTEGER,
                dtmbModulationDualPilotTone
                    SwitchOnOff,
                dtmbModulationGuardIntervalPN
                    INTEGER
             }

        dtmbModulationChannelBandwidth OBJECT-TYPE
            SYNTAX DtmbChannelBandwidth
            MAX-ACCESS read-write
            STATUS current
            DESCRIPTION
                "Channel bandwidth occupied by the DTMB signal in the frequency spectrum. 
                6 MHz, 7 MHz or 8 MHz can be set. 
                The choice depends on the required bandwidth of the channel to be transmitted. "
            ::= { dtmbModulationEntry 3 }

        
        dtmbModulationGuardInterval OBJECT-TYPE
            SYNTAX DtmbGuardInterval
            MAX-ACCESS read-write
            STATUS current
            DESCRIPTION
                "Padding mode for the guard interval. 
                The value can be changed if Manual was selected as the TPS source."
            ::= { dtmbModulationEntry 5 }

        
        dtmbModulationConstellation OBJECT-TYPE
            SYNTAX DtmbModulation
            MAX-ACCESS read-write
            STATUS current
            DESCRIPTION
                "Sets up the modulation mode.
                The value can be changed if Manual was selected as the TPS source."
            ::= { dtmbModulationEntry 6 }

        
        dtmbModulationCodeRate OBJECT-TYPE
            SYNTAX DtmbCodeRate
            MAX-ACCESS read-write
            STATUS current
            DESCRIPTION
                "Sets the code rate. The code rate is used to set 
                the ratio of information data to (error correction values + information data). 
                4/10 provides the greatest error correction and the lowest data transfer rate 
                8/10 provides the lowest error correction and the greatest data transfer rate. 
                The value can be changed if Manual was selected as the TPS source.
                "
            ::= { dtmbModulationEntry 7 }

        
        dtmbModulationTimeInterleaver OBJECT-TYPE
            SYNTAX INTEGER
                {
                off(2),
                s240(3),
                s720(4)
                }
            MAX-ACCESS read-write
            STATUS current
            DESCRIPTION
                "Sets the mode for the time interleaver. 
                The time interleaver distributes the payload data over 
                many symbols in order to reduce noise sensitivity. 
                The setting 720 symbols (s720-3) is recommended for 
                a high error tolerance. If, on the other hand, the resulting 
                delay is to be kept short, the setting 240 symbols (s240-2) is more suitable. 
                The value can be changed if Manual was selected as the TPS source."
            ::= { dtmbModulationEntry 8 }

        
        dtmbModulationControlFrame OBJECT-TYPE
            SYNTAX SwitchOnOff
            MAX-ACCESS read-write
            STATUS obsolete
            DESCRIPTION
                "obsolete parameter. "
            ::= { dtmbModulationEntry 9 }

        
        dtmbModulationCarrierMode OBJECT-TYPE
            SYNTAX INTEGER
                {
                single(2),
                multi(3)
                }
            MAX-ACCESS read-write
            STATUS current
            DESCRIPTION
                "configures whether the signal should be transmitted in 
                Single Carrier Mode (previously: ADTB-T) or in 
                Multicarrier Mode (previously: DMB-T) with 3780 single carriers."
            ::= { dtmbModulationEntry 10 }

        
        dtmbModulationDualPilotTone OBJECT-TYPE
            SYNTAX SwitchOnOff
            MAX-ACCESS read-write
            STATUS current
            DESCRIPTION
                "configures whether two additional pilot signals are to be inserted into the spectrum. 
                The pilots are at +/- half symbol rate. 
                The setting can be changed here. 
                This parameter is effective only if Carrier Mode= Single has been selected."
            ::= { dtmbModulationEntry 11 }

        
        dtmbModulationGuardIntervalPN OBJECT-TYPE
            SYNTAX INTEGER
                {
                variable(2),
                constant(3)
                }
            MAX-ACCESS read-write
            STATUS current
            DESCRIPTION
                "Sets which PN sequence (pseudo random noise sequence) 
                is used for the guard interval. 
                Constant (3): The PN sequence Index 0 is always used 
                Variable (2): All PN sequences will be used. 
                "
            ::= { dtmbModulationEntry 12 }

        
        dtmbTestTable OBJECT-TYPE
            SYNTAX SEQUENCE OF DtmbTestEntry
            MAX-ACCESS not-accessible
            STATUS current
            DESCRIPTION
                "Configures the test mode of the exciter."
            ::= { dtmbSetup 4 }

        
        dtmbTestEntry OBJECT-TYPE
            SYNTAX DtmbTestEntry
            MAX-ACCESS not-accessible
            STATUS current
            DESCRIPTION
                "An entry in the dtmbTestTable."
            AUGMENTS { dtmbConfigurationEntry }
            ::= { dtmbTestTable 1 }

        
        DtmbTestEntry ::=
            SEQUENCE { 
                dtmbTestMode
                    INTEGER,
                dtmbTestCarrierPower
                    Unsigned32
             }

        dtmbTestMode OBJECT-TYPE
            SYNTAX INTEGER
                {
                off(1),
                prbs(2),
                singleCarrier(3)
                }
            MAX-ACCESS read-write
            STATUS current
            DESCRIPTION
                "sets which test signal is to be generated.
                - Off (1): switches off test signal generation.
                - PRBS (2): Generates a pseudo-random binary sequence insted of the payload.
                - Single Carrier (3): Generates an unmodulated single carrier. 
                This test signal can be used to measure the phase noise of the synthesizer. 
                The phase noise must be measured via the RF Monitor Out connector (X61). 
                The cable connected to RF Out (X60) must be removed. In order to protect the amplifiers, 
                this test signal is only generated if the output of the exciter is open."
            ::= { dtmbTestEntry 1 }

        
        dtmbTestCarrierPower OBJECT-TYPE
            SYNTAX Unsigned32 (0..255)
            MAX-ACCESS read-write
            STATUS current
            DESCRIPTION
                "sets level of the single carrier. This parameter is effective 
                only if Carrier Mode = Single has been selected. "
            ::= { dtmbTestEntry 2 }

        
        dtmbLocalizationTable OBJECT-TYPE
            SYNTAX SEQUENCE OF DtmbLocalizationEntry
            MAX-ACCESS not-accessible
            STATUS current
            DESCRIPTION
                "DTMB localization parameters.
                "
            ::= { dtmbSetup 5 }

        
        dtmbLocalizationEntry OBJECT-TYPE
            SYNTAX DtmbLocalizationEntry
            MAX-ACCESS not-accessible
            STATUS current
            DESCRIPTION
                "An entry in the dtmbLocalizationTable."
            INDEX { dtmbConfigurationTxIdx, dtmbConfigurationExcIdx }
            ::= { dtmbLocalizationTable 1 }

        
        DtmbLocalizationEntry ::=
            SEQUENCE { 
                dtmbLocalizationTxControl
                    INTEGER,
                dtmbLocalizationTxAddress
                    Unsigned32
             }

        dtmbLocalizationTxControl OBJECT-TYPE
            SYNTAX INTEGER
                {
                undefined(1),
                on(2),
                off(3)
                }
            MAX-ACCESS read-write
            STATUS current
            DESCRIPTION
                "Description."
            ::= { dtmbLocalizationEntry 1 }

        
        dtmbLocalizationTxAddress OBJECT-TYPE
            SYNTAX Unsigned32 (0..65535)
            MAX-ACCESS read-write
            STATUS current
            DESCRIPTION
                "Description."
            ::= { dtmbLocalizationEntry 2 }

        
        dtmbOutput OBJECT IDENTIFIER ::= { rsXx9DtmbObjects 3 }

        
        dtmbOutModulationTable OBJECT-TYPE
            SYNTAX SEQUENCE OF DtmbOutModulationEntry
            MAX-ACCESS not-accessible
            STATUS current
            DESCRIPTION
                "Currently active DTMB modulation parameters."
            ::= { dtmbOutput 1 }

        
        dtmbOutModulationEntry OBJECT-TYPE
            SYNTAX DtmbOutModulationEntry
            MAX-ACCESS not-accessible
            STATUS current
            DESCRIPTION
                "An entry in the dtmbOutModulationTable."
            INDEX { dtmbConfigurationTxIdx, dtmbConfigurationExcIdx }
            ::= { dtmbOutModulationTable 1 }

        
        DtmbOutModulationEntry ::=
            SEQUENCE { 
                dtmbOutModulationChannelBandwidth
                    DtmbChannelBandwidth,
                dtmbOutModulationGuardInterval
                    DtmbGuardInterval,
                dtmbOutModulationConstellation
                    DtmbModulation,
                dtmbOutModulationCodeRate
                    DtmbCodeRate,
                dtmbOutModulationTimeInterleaver
                    INTEGER,
                dtmbOutModulationCarrierMode
                    INTEGER,
                dtmbOutModulationDualPilotTone
                    SwitchOnOff,
                dtmbOutModulationGuardIntervalPN
                    INTEGER
             }

        dtmbOutModulationChannelBandwidth OBJECT-TYPE
            SYNTAX DtmbChannelBandwidth
            MAX-ACCESS read-only
            STATUS current
            DESCRIPTION
                "Channel bandwidth occupied by the DTMB signal in the frequency spectrum. 
                6 MHz, 7 MHz or 8 MHz can be set. 
                The choice depends on the required bandwidth of the channel to be transmitted. "
            ::= { dtmbOutModulationEntry 3 }

        
        dtmbOutModulationGuardInterval OBJECT-TYPE
            SYNTAX DtmbGuardInterval
            MAX-ACCESS read-only
            STATUS current
            DESCRIPTION
                "Padding mode for the guard interval. 
                The value can be changed if Manual was selected as the TPS source."
            ::= { dtmbOutModulationEntry 5 }

        
        dtmbOutModulationConstellation OBJECT-TYPE
            SYNTAX DtmbModulation
            MAX-ACCESS read-only
            STATUS current
            DESCRIPTION
                "Shows the modulation mode.
                The value can be changed if Manual was selected as the TPS source."
            ::= { dtmbOutModulationEntry 6 }

        
        dtmbOutModulationCodeRate OBJECT-TYPE
            SYNTAX DtmbCodeRate
            MAX-ACCESS read-only
            STATUS current
            DESCRIPTION
                "Shows the code rate. The code rate is used to set 
                the ratio of information data to (error correction values + information data). 
                4/10 provides the greatest error correction and the lowest data transfer rate 
                8/10 provides the lowest error correction and the greatest data transfer rate. 
                The value can be changed if Manual was selected as the TPS source.
                "
            ::= { dtmbOutModulationEntry 7 }

        
        dtmbOutModulationTimeInterleaver OBJECT-TYPE
            SYNTAX INTEGER
                {
                off(2),
                s240(3),
                s720(4)
                }
            MAX-ACCESS read-only
            STATUS current
            DESCRIPTION
                "Shows the mode for the time interleaver. 
                The time interleaver distributes the payload data over 
                many symbols in order to reduce noise sensitivity. 
                The setting 720 symbols (s720-3) is recommended for 
                a high error tolerance. If, on the other hand, the resulting 
                delay is to be kept short, the setting 240 symbols (s240-2) is more suitable. 
                The value can be changed if Manual was selected as the TPS source."
            ::= { dtmbOutModulationEntry 8 }

        
        dtmbOutModulationCarrierMode OBJECT-TYPE
            SYNTAX INTEGER
                {
                single(2),
                multi(3)
                }
            MAX-ACCESS read-only
            STATUS current
            DESCRIPTION
                "Shows whether the signal should be transmitted in 
                Single Carrier Mode (previously: ADTB-T) or in 
                Multicarrier Mode (previously: DMB-T) with 3780 single carriers."
            ::= { dtmbOutModulationEntry 10 }

        
        dtmbOutModulationDualPilotTone OBJECT-TYPE
            SYNTAX SwitchOnOff
            MAX-ACCESS read-only
            STATUS current
            DESCRIPTION
                "Shows whether two additional pilot signals are to be inserted into the spectrum. 
                The pilots are at +/- half symbol rate. 
                This parameter is effective only if Carrier Mode= Single has been selected."
            ::= { dtmbOutModulationEntry 11 }

        
        dtmbOutModulationGuardIntervalPN OBJECT-TYPE
            SYNTAX INTEGER
                {
                variable(2),
                constant(3)
                }
            MAX-ACCESS read-only
            STATUS current
            DESCRIPTION
                "Shows which PN sequence (pseudo random noise sequence) 
                is used for the guard interval. 
                Constant (3): The PN sequence Index 0 is always used 
                Variable (2): All PN sequences will be used. 
                "
            ::= { dtmbOutModulationEntry 12 }

        
        rsXx9DtmbConformance OBJECT IDENTIFIER ::= { rsXx9Dtmb 2 }

        
        rsXx9DtmbCompliances OBJECT IDENTIFIER ::= { rsXx9DtmbConformance 1 }

        
        dtmbBasicCompliance MODULE-COMPLIANCE
            STATUS current
            DESCRIPTION 
                "The compliance statement for XX9000 DTMB encoding."
            MODULE -- this module
                MANDATORY-GROUPS { dtmbObjBasic }
            ::= { rsXx9DtmbCompliances 1 }

        
        rsXx9DtmbGroups OBJECT IDENTIFIER ::= { rsXx9DtmbConformance 2 }

        
        dtmbObjBasic OBJECT-GROUP
            OBJECTS { dtmbConfigurationTpsSource, dtmbModulationChannelBandwidth, dtmbModulationGuardInterval, dtmbModulationConstellation, dtmbModulationCodeRate, 
                dtmbModulationTimeInterleaver, dtmbModulationCarrierMode, dtmbModulationDualPilotTone, dtmbModulationGuardIntervalPN, dtmbStTxDelayOffset, 
                dtmbOutModulationChannelBandwidth, dtmbOutModulationGuardInterval, dtmbOutModulationConstellation, dtmbOutModulationCodeRate, dtmbOutModulationTimeInterleaver, 
                dtmbOutModulationCarrierMode, dtmbOutModulationDualPilotTone, dtmbOutModulationGuardIntervalPN, dtmbLocalizationTxAddress, dtmbLocalizationTxControl, 
                dtmbTestMode, dtmbStatusNotificationName, dtmbStatusNotificationMask, dtmbStatusNotificationPriority, dtmbStatusNotificationState, 
                dtmbConfigurationInfoPacketReplacement, dtmbConfigurationNetworkMode, dtmbTestCarrierPower }
            STATUS current
            DESCRIPTION 
                "Basic DTMB objects group."
            ::= { rsXx9DtmbGroups 1 }

        
        dtmbNotifyBasic NOTIFICATION-GROUP
            NOTIFICATIONS { dtmbEncoderSummary, dtmbManualConfiguration, dtmbActiveConfiguration, dtmbTest }
            STATUS current
            DESCRIPTION 
                "General DTMB notifications."
            ::= { rsXx9DtmbGroups 2 }

        
        dtmbObjBasicObsolete OBJECT-GROUP
            OBJECTS { dtmbModulationControlFrame }
            STATUS obsolete
            DESCRIPTION 
                "absoleted DTMB objects group."
            ::= { rsXx9DtmbGroups 3 }

        
    
    END

--
-- RS-XX9-DTMB-MIB.mi2
--
