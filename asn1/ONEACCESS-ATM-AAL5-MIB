--          *****************************
--          *                           *
--          *         ONEOS MIB         *
--          *                           *
--          *****************************
--
--          ONEOS_MIB_STD_V05.1.R005_E0001
--
--          Creation date : 10/04/2006 (TF2967)
--
--------------------------------------------------------------------
 
    ONEACCESS-ATM-AAL5-MIB DEFINITIONS ::= BEGIN
 
--------------------------------------------------------------------
-- Imports
--------------------------------------------------------------------
    IMPORTS
        InterfaceIndex, ifIndex
            FROM IF-MIB
        MODULE-IDENTITY, OBJECT-TYPE, Integer32
            FROM SNMPv2-SMI
		MODULE-COMPLIANCE, OBJECT-GROUP
			FROM SNMPv2-CONF
        atmVclVpi, atmVclVci
            FROM ATM-MIB
        oacExpIMAtmAal5, oacMIBModules, oacRequirements
            FROM ONEACCESS-GLOBAL-REG
        ;
 
--------------------------------------------------------------------
-- Module Entity
--------------------------------------------------------------------
oacAtmAal5MIBModule MODULE-IDENTITY
LAST-UPDATED "201110270000Z"
ORGANIZATION " OneAccess "
CONTACT-INFO
"Pascal KESTELOOT
Postal: ONE ACCESS
381 Avenue du Général de Gaulle
92140 Clamart, France
FRANCE
 
Tel: (+33) 01 41 87 70 00
Fax: (+33) 01 41 87 74 00
 
E-mail: pascal.kesteloot@oneaccess-net.com"

DESCRIPTION
                "Contact updated"
REVISION        "201110270000Z"

DESCRIPTION
"Fixed compilation errors and warnings."

REVISION	"201007081000Z"

DESCRIPTION
"This MIB module describes ATM AAL5 objects."


::= { oacMIBModules 800 }
 
--------------------------------------------------------------------
-- Objects Definitions
--------------------------------------------------------------------
oacExpIMAtmAal5Objects    OBJECT IDENTIFIER ::= { oacExpIMAtmAal5 1 }
oacExpIMAtmAal5Notifications  OBJECT IDENTIFIER ::= { oacExpIMAtmAal5 2 }
 
    --------------------------------------------------------------------
    -- Control Table Definition
    --------------------------------------------------------------------
oacExpIMAtmAal5VclLogicalIndexTable OBJECT-TYPE
SYNTAX SEQUENCE OF OacExpIMAtmAal5VclLogicalIndexEntry
MAX-ACCESS not-accessible
STATUS current
DESCRIPTION
" Table to get a link between Port/Vp/Vc and OneOs
ifTable index of logical interface"
::= { oacExpIMAtmAal5Objects 1 }
 
oacExpIMAtmAal5VclLogicalIndexEntry OBJECT-TYPE
SYNTAX OacExpIMAtmAal5VclLogicalIndexEntry
MAX-ACCESS not-accessible
STATUS current
DESCRIPTION
" indexes are taken from atmVclTable "
INDEX  {ifIndex, atmVclVpi, atmVclVci }
::= { oacExpIMAtmAal5VclLogicalIndexTable 1 }
 
OacExpIMAtmAal5VclLogicalIndexEntry ::= SEQUENCE {
oacExpIMAtmAal5VclLogicalIndexIfIndex InterfaceIndex
}
 
oacExpIMAtmAal5VclLogicalIndexIfIndex OBJECT-TYPE
SYNTAX      InterfaceIndex
MAX-ACCESS  read-only
STATUS      current
DESCRIPTION
"The ifTable index of the ATM logical port interface
associated with the VP/VC."
::= { oacExpIMAtmAal5VclLogicalIndexEntry 1 }
 
--------------------------------------------------------------------
-- Conformance Definitions
--------------------------------------------------------------------
    oacExpIMAtmAal5Conformance OBJECT IDENTIFIER ::= { oacRequirements 800 }
    oacExpIMAtmAal5Groups      OBJECT IDENTIFIER ::= { oacExpIMAtmAal5Conformance 1 }
    oacExpIMAtmAal5Compliances OBJECT IDENTIFIER ::= { oacExpIMAtmAal5Conformance 2 }
 
    oacExpIMAtmAal5Compliance MODULE-COMPLIANCE
        STATUS  current
        DESCRIPTION
            "The compliance statement for agents that support the
             ONEACCESS-ATM-AAL5-MIB."
        MODULE -- this module
        MANDATORY-GROUPS { oacExpIMAtmAal5GeneralGroup }
    ::= { oacExpIMAtmAal5Compliances 1}
 
    oacExpIMAtmAal5GeneralGroup OBJECT-GROUP
    OBJECTS {
oacExpIMAtmAal5VclLogicalIndexIfIndex
        }
        STATUS  current
        DESCRIPTION
            "This group is mandatory for ATM AAL5 entity."
        ::= { oacExpIMAtmAal5Groups 1 }
 
END
