ACOS-VRRPA-PARTITION-VRID-ALL-STATUS-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		vrrpAPartitionVridAllStatusModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "vrrpAPartitionVridAllStatusModule OID for ACOS"
				::=  {  acosSchema 9 }

partitionVridAllStatus		 OBJECT IDENTIFIER ::= { vrrpAPartitionVridAllStatusModule 1}

partitionVridAllStatusOperAllPartitionListTable OBJECT-TYPE
	 SYNTAX SEQUENCE OF PartitionVridAllStatusOperAllPartitionListEntry
	 MAX-ACCESS not-accessible
	 STATUS current
	 DESCRIPTION
		 "display vrid all status for all partitions from object 'vrrp-a.partition-vrid-all-status'"
	::= {partitionVridAllStatus 2}

partitionVridAllStatusOperAllPartitionListEntry OBJECT-TYPE
	SYNTAX PartitionVridAllStatusOperAllPartitionListEntry
	MAX-ACCESS not-accessible
	STATUS current
	DESCRIPTION
		"The partitionVridAllStatusOperAllPartitionList entry:all-partition-list"
	INDEX {
		partitionVridAllStatusOperAllPartitionListSlotId,
		partitionVridAllStatusOperAllPartitionListAllPartitionListListId
	}
	::= { partitionVridAllStatusOperAllPartitionListTable 1}

PartitionVridAllStatusOperAllPartitionListEntry ::=
	SEQUENCE {
		partitionVridAllStatusOperAllPartitionListSlotId Integer32,
		partitionVridAllStatusOperAllPartitionListAllPartitionListListId Integer32,
		partitionVridAllStatusOperAllPartitionListLocalDeviceID	Integer32,
		partitionVridAllStatusOperAllPartitionListPartitionName	DisplayString,
		partitionVridAllStatusOperAllPartitionListVrid	Integer32,
		partitionVridAllStatusOperAllPartitionListActiveDeviceId	Integer32,
		partitionVridAllStatusOperAllPartitionListActivePriority	Integer32,
		partitionVridAllStatusOperAllPartitionListActiveWeight	Integer32,
		partitionVridAllStatusOperAllPartitionListStandbyDeviceId	Integer32,
		partitionVridAllStatusOperAllPartitionListStandbyPriority	Integer32,
		partitionVridAllStatusOperAllPartitionListStandbyWeight	Integer32
	}

partitionVridAllStatusOperAllPartitionListSlotId OBJECT-TYPE
	SYNTAX Integer32
	MAX-ACCESS read-only
	STATUS current
	DESCRIPTION
		""
	::= { partitionVridAllStatusOperAllPartitionListEntry 1}

partitionVridAllStatusOperAllPartitionListAllPartitionListListId OBJECT-TYPE
	SYNTAX Integer32
	MAX-ACCESS read-only
	STATUS current
	DESCRIPTION
		""
	::= { partitionVridAllStatusOperAllPartitionListEntry 2}

partitionVridAllStatusOperAllPartitionListLocalDeviceID OBJECT-TYPE
	SYNTAX Integer32
	MAX-ACCESS read-only
	STATUS current
	DESCRIPTION
		"local_device_ID"
	::= { partitionVridAllStatusOperAllPartitionListEntry 3}

partitionVridAllStatusOperAllPartitionListPartitionName OBJECT-TYPE
	SYNTAX DisplayString
	MAX-ACCESS read-only
	STATUS current
	DESCRIPTION
		"partition-name"
	::= { partitionVridAllStatusOperAllPartitionListEntry 4}

partitionVridAllStatusOperAllPartitionListVrid OBJECT-TYPE
	SYNTAX Integer32
	MAX-ACCESS read-only
	STATUS current
	DESCRIPTION
		"vrid"
	::= { partitionVridAllStatusOperAllPartitionListEntry 5}

partitionVridAllStatusOperAllPartitionListActiveDeviceId OBJECT-TYPE
	SYNTAX Integer32
	MAX-ACCESS read-only
	STATUS current
	DESCRIPTION
		"active_device_id"
	::= { partitionVridAllStatusOperAllPartitionListEntry 6}

partitionVridAllStatusOperAllPartitionListActivePriority OBJECT-TYPE
	SYNTAX Integer32
	MAX-ACCESS read-only
	STATUS current
	DESCRIPTION
		"active_priority"
	::= { partitionVridAllStatusOperAllPartitionListEntry 7}

partitionVridAllStatusOperAllPartitionListActiveWeight OBJECT-TYPE
	SYNTAX Integer32
	MAX-ACCESS read-only
	STATUS current
	DESCRIPTION
		"active_weight"
	::= { partitionVridAllStatusOperAllPartitionListEntry 8}

partitionVridAllStatusOperAllPartitionListStandbyDeviceId OBJECT-TYPE
	SYNTAX Integer32
	MAX-ACCESS read-only
	STATUS current
	DESCRIPTION
		"standby_device_id"
	::= { partitionVridAllStatusOperAllPartitionListEntry 9}

partitionVridAllStatusOperAllPartitionListStandbyPriority OBJECT-TYPE
	SYNTAX Integer32
	MAX-ACCESS read-only
	STATUS current
	DESCRIPTION
		"standby_priority"
	::= { partitionVridAllStatusOperAllPartitionListEntry 10}

partitionVridAllStatusOperAllPartitionListStandbyWeight OBJECT-TYPE
	SYNTAX Integer32
	MAX-ACCESS read-only
	STATUS current
	DESCRIPTION
		"standby_weight"
	::= { partitionVridAllStatusOperAllPartitionListEntry 11}

END
