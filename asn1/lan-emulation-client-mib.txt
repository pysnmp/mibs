LAN-EMULATION-CLIENT-MIB DEFINITIONS ::= BEGIN


    IMPORTS

        MODULE-IDENTITY, OBJECT-TYPE,
        enterprises, Counter32, Integer32      FROM SNMPv2-SMI

        TEXTUAL-CONVENTION, MacAddress,
        RowStatus, TruthValue, DisplayString   FROM SNMPv2-TC

        MODULE-COMPLIANCE, OBJECT-GROUP        FROM SNMPv2-CONF

        ifIndex                                FROM RFC1213-MIB

        OwnerString                            FROM RFC1271-MIB;



    -- ------------------------------------------------------------ --
    --
    --  The following OBJECT IDENTIFIER definition should be moved to
    --  some other location, to conform with the statement in RFC 1442
    --  that the MODULE-IDENTITY section must appear immediately after
    --  any IMPORTs or EXPORTs statements.
    --
    --  However, some MIB utilities don't like MODULE-IDENTITY OIDs of
    --  the form { enterprises atmForum(353) ... 1 }.  Separate OBJECT
    --  IDENTIFIER definitions appear to be more widely accepted - so,
    --  in the interests of compatibility, it remains.
    --
    -- ------------------------------------------------------------ --


    leClientMIB MODULE-IDENTITY
        LAST-UPDATED "9505100000Z"
        ORGANIZATION "ATM Forum LAN Emulation Sub-Working Group"
        CONTACT-INFO
              "
                The ATM Forum
                303 Vintage Park Drive
                Foster City, CA  94404
                United States of America
                Tel: 415-578-6860
                E-mail: info@atmforum.com"
        DESCRIPTION
            "This module defines a portion of the management 
             information base (MIB) for managing ATM LAN Emulation
             Client nodes.  It is meant to be used in connection with
             the AToM MIB and MIB-II / RFC 1573 'ifTable' entries
             for each LEC / emulated 802.x network interface."
        ::= { enterprises
                 atmForum(353)
                    atmForumNetworkManagement(5)
                       3
                          1 }

    -- The object identifier subtree for ATM Forum LAN Emulation MIBs
    atmfLanEmulation  OBJECT IDENTIFIER ::= {
                                      atmForumNetworkManagement
                                         3
                      }


    leClientMIBObjects  OBJECT IDENTIFIER ::= { leClientMIB 1 }


    -- This MIB module consists of the following groups:
    --
    --  (1) LAN Emulation Client groups
    --      (a) Configuration group
    --      (b) Status group
    --      (c) Statistics group
    --      (d) Server VCC group
    --
    --  (2) LEC ATM Addresses group
    --
    --  (3) Registered LAN Destination groups
    --      (a) MAC addresses group
    --      (b) Route Descriptors group
    --
    --  (4) LE_ARP cache groups
    --      (a) MAC address cache group
    --      (b) Route descriptor cache group
    --
    --  (5) ifIndex mapping group
    --
    -- Security management objects have been explicitly omitted from
    -- this MIB as being outside the scope of the V1.0 LAN Emulation
    -- specification.


    AtmLaneAddress ::= TEXTUAL-CONVENTION
        STATUS     current
        DESCRIPTION
              "A twenty-octet binary string, containing a standard
               ATM Forum address -- or the zero-length string,
               indicating the absence of an address.

               For LAN Emulation purposes, the eight-octet address
               format is not used."
        SYNTAX     OCTET STRING ( SIZE( 0 | 20 ) )

    VpiInteger ::= TEXTUAL-CONVENTION
        STATUS     current
        DESCRIPTION
              "An integer large enough to hold a VPI."
        SYNTAX     INTEGER ( 0..255 )

    VciInteger ::= TEXTUAL-CONVENTION
        STATUS     current
        DESCRIPTION
              "An integer large enough to hold a VCI."
        SYNTAX     INTEGER ( 0..65535 )

    LeConnectionInterface ::= TEXTUAL-CONVENTION
        STATUS     current
        DESCRIPTION
                "A combination flag and ifTable index, indicating
                 whether a LAN Emulation circuit exists - and, if
                 so, which interface is associated with it at the
                 point where it connects to a LE Client.

                 Objects of this type are always defined as part of
                 a set that includes

                         fooInterface   LeConnectionInterface
                         fooVpi         VpiInteger
                         fooVci         VciInteger

                 The interpretation of these objects is as follows.

                 1.  If no connection exists, 'fooInterface' has a
                     value of 0.  Because Interfaces table entries
                     always have 'ifIndex' values larger than 0,
                     'fooInterface' reliably serves as a 'connection
                     exists' flag.

                     In this case, 'fooVpi' and 'fooVci' are
                     meaningless, and have the value 0.

                 2.  If a PVC or SVC exists, 'fooInterface' is defined
                     to have the value of the MIB-II/RFC 1573 'ifIndex'
                     of the 'atm' interface associated with the VCC.
                     'fooVpi' and 'fooVci' will contain its VPI/VCI.
                     Therefore, ('fooInterface', 'fooVpi', 'fooVci')
                     give you an index into the AToM MIB which allows
                     you to examine and play with the circuit further.

                  3. If a proprietary connection (such as an internal
                     data path between co-located components) exists,
                     this specification does not mandate how it should
                     be managed.  One option is to set 'fooInterface'
                     to the value of the MIB-II/RFC 1573 'ifIndex' for
                     the LAN Emulation Client.  This indicates that a
                     connection exists, but is not being managed in the
                     same fashion as an ATM VCC."
        SYNTAX   INTEGER ( 0..2147483647 )

    LecState ::= TEXTUAL-CONVENTION
        STATUS     current
        DESCRIPTION
              "An official protocol state of a LAN Emulation Client."
        REFERENCE
              "ATM Forum LAN Emulation Over ATM Specification, V1.0,
               Section 2.3.1"
        SYNTAX     INTEGER {
                             initialState(1),
                             lecsConnect(2),
                             configure(3),
                             join(4),
                             initialRegistration(5),
                             busConnect(6),
                             operational(7)
                            }

    LecDataFrameFormat ::= TEXTUAL-CONVENTION
        STATUS     current
        DESCRIPTION
              "A 'LAN Type' value.

               C2  LAN Type.  The type of LAN that the LE Client is,
                   or wishes to become, a member of.  This MUST be one
                   of Ethernet/IEEE 802.3, IEEE 802.5, or Unspecified."
        REFERENCE
              "ATM Forum LAN Emulation Over ATM Specification, V1.0,
               Section 5.1.1"
        SYNTAX      INTEGER {
                             unspecified(1),
                             aflane8023(2),
                             aflane8025(3)
                            }

    LecDataFrameSize ::= TEXTUAL-CONVENTION
        STATUS     current
        DESCRIPTION
              "A 'Maximum Data Frame Size' value.

               C3  Maximum Data Frame Size.  The maximum AAL-5 SDU size
                   of a data frame that the LE Client wishes to send on
                   the Multicast Send VCC or to receive on the
                   Multicast Send VCC or Multicast Forward VCC.  This
                   parameter also specifies the maximum AAL-5 SDU on
                   all of a LE Client's Data Direct VCCs.  This MUST be
                   either 1516, 4544, 9234, or 18190 octets, or
                   Unspecified."
        REFERENCE
              "ATM Forum LAN Emulation Over ATM Specification, V1.0,
               Section 5.1.1"
        SYNTAX      INTEGER {
                             unspecified(1),
                             max1516(2),
                             max4544(3),
                             max9234(4),
                             max18190(5)
                            }

    LeArpTableEntryType ::= TEXTUAL-CONVENTION
        STATUS     current
        DESCRIPTION
                "Indicates how a LE_ARP table entry was created and
                 whether it is subject to aging.

                     other(1)
                         The LE_ARP entry does not fall into one of
                         the categories defined below.

                     learnedViaControl(2)
                         This LE_ARP entry was learned by using the
                         LE_ARP_REQUEST / LE_ARP_RESPONSE protocol,
                         or by otherwise observing relevant traffic
                         on Control VCCs.

                         Entries of this type are aged.

                     learnedViaData(3)
                         This LE_ARP entry was learned by observing
                         incoming traffic on Data VCCs.

                         Entries of this type are aged.

                     staticVolatile(4)
                         This LE_ARP entry was created by management.
                         It will not be aged.  On the other hand, it
                         will not survive a restart of the client.

                         If an agent permits LE_ARP entries of this
                         type to be created, it may require that the
                         LAN Emulation Client be in the 'operational'
                         state at the time.

                     staticNonVolatile(5)
                         This LE_ARP entry was created by management.
                         It will not be aged, and it will survive a
                         restart of the client.

                 The values 'learnedViaData' and 'learnedViaControl'
                 can be read, but may not be written."
        SYNTAX      INTEGER {
                             other(1),
                             learnedViaControl(2),
                             learnedViaData(3),
                             staticVolatile(4),
                             staticNonVolatile(5)
                            }


    -- ------------------------------------------------------------- --

    --
    --  LAN Emulation Client configuration group
    --

    lecConfigTable OBJECT-TYPE
        SYNTAX       SEQUENCE OF LecConfigEntry
        MAX-ACCESS   not-accessible
        STATUS       current
        DESCRIPTION
                "A table describing all of the LAN Emulation Clients
                 implemented by this host.  Each LE Client has a row
                 in the MIB-II/RFC 1573 Interfaces table (describing
                 the emulated packet interface it presents to higher
                 layers).  Each LE Client also has a row in this and
                 other LEC MIB tables (describing its interface with
                 other LAN Emulation components).

                 This table contains configuration variables.  Three
                 extension tables contain client status, performance
                 statistics, and information about control/multicast
                 VCCs.

                 Unlike hardware ports, LE Clients can be created by
                 management.  However, the RFC 1573 Interfaces table
                 does not directly support row creation.  Therefore,
                 creating or deleting a row in the lecConfigTable is
                 defined to have the side effect of creating or
                 deleting corresponding rows in

                     -  the MIB-II / RFC 1573 Interfaces table,
                     -  the 'lecMappingTable',
                     -  the 'lecStatusTable',
                     -  the 'lecServerVccTable',
                     -  the 'lecStatisticsTable', and
                     -  any other dependent tables

                 New Interfaces table rows for LAN Emulation Clients
                 always have 'ifAdminStatus' set to 'down'.


                 A Note On Indexing:
                 -------------------
                 Most of the tables in this MIB are indexed in whole
                 or in part by 'lecIndex' - not by 'ifIndex'.

                 Why is there a separate index?

                 Traditionally, ifIndex values are chosen by agents,
                 and are permitted to change across restarts.  Using
                 ifIndex to index lecConfigTable could complicate
                 row creation and/or cause interoperability problems
                 (if each agent had special restrictions on ifIndex).
                 Having a separate index avoids these problems.      "
        ::= { leClientMIBObjects 1 }

    lecConfigEntry OBJECT-TYPE
        SYNTAX       LecConfigEntry
        MAX-ACCESS   not-accessible
        STATUS       current
        DESCRIPTION
                "Each table entry contains configuration information
                 for one LAN Emulation Client.

                 Most of the objects are derived from Initial State
                 Parameters in the LAN Emulation specification."
        INDEX   { lecIndex }
        ::= { lecConfigTable 1 }

    LecConfigEntry ::=
        SEQUENCE {

            --
            --  Row indices, creation, and deletion.
            --
            lecIndex                    INTEGER,
            lecRowStatus                RowStatus,
            lecOwner                    OwnerString,

            --
            --  Key parameters for Configure / Join phase.  Note that
            --  these are not operational values - see lecStatusTable
            --  for those.
            --
            lecConfigMode               INTEGER,
            lecConfigLanType            LecDataFrameFormat,
            lecConfigMaxDataFrameSize   LecDataFrameSize,
            lecConfigLanName            DisplayString,
            lecConfigLesAtmAddress      AtmLaneAddress,

            --
            --  Other parameters.  These may be changed either by the
            --  network manager or by the LE Configuration Server.
            --
            lecControlTimeout           INTEGER,
            lecMaxUnknownFrameCount     INTEGER,
            lecMaxUnknownFrameTime      INTEGER,
            lecVccTimeoutPeriod         Integer32,
            lecMaxRetryCount            INTEGER,
            lecAgingTime                INTEGER,
            lecForwardDelayTime         INTEGER,
            lecExpectedArpResponseTime  INTEGER,
            lecFlushTimeOut             INTEGER,
            lecPathSwitchingDelay       INTEGER,
            lecLocalSegmentID           INTEGER,
            lecMulticastSendType        INTEGER,
            lecMulticastSendAvgRate     Integer32,
            lecMulticastSendPeakRate    Integer32,
            lecConnectionCompleteTimer  INTEGER

        }

    lecIndex OBJECT-TYPE
        SYNTAX      INTEGER ( 1..2147483647 )
        MAX-ACCESS  not-accessible
        STATUS      current
        DESCRIPTION
                "A value which uniquely identifies this conceptual
                 row in the lecConfigTable.

                 If the conceptual row identified by this value of
                 lecIndex is recreated following an agent restart,
                 the same value of lecIndex must be used to identify
                 the recreated row.  (However, the Interfaces table
                 index associated with the client may change.)"
        ::= { lecConfigEntry 1 }

    lecRowStatus OBJECT-TYPE
        SYNTAX      RowStatus
        MAX-ACCESS  read-create
        STATUS      current
        DESCRIPTION
                "This object lets network managers create and delete
                 LAN Emulation Clients, on systems that support this
                 optional capability.

                 It does not control Joins and Terminations; they are
                 controlled by 'ifAdminStatus'.  However, taking rows
                 out of service will have the side effect of changing
                 their 'ifAdminStatus' values to 'down', thus causing
                 any active emulated LAN connections to be terminated.

                 Within each conceptual lecConfigTable row, objects
                 which are writable may be modified regardless of the
                 value of lecRowStatus.  It is not necessary to set a
                 row's status to 'notInService' first.

                 When creating a LAN Emulation Client, it is up to the
                 management station to determine a suitable 'lecIndex'.
                 To facilitate interoperability, agents should not put
                 any restrictions on the 'lecIndex' beyond the obvious
                 ones that it be valid and unused.

                 If you create a LAN Emulation Client via this object,
                 it will initially have

                     'ifAdminStatus' = 'down'
                     'ifOperStatus' = 'down'
                     'lecInterfaceState' = 'initialState'            "
        ::= { lecConfigEntry 2 }

    lecOwner OBJECT-TYPE
        SYNTAX      OwnerString( SIZE (0..127) )
        MAX-ACCESS  read-create
        STATUS      current
        DESCRIPTION
                "The entity that configured this entry and is therefore
                 using the resources assigned to it."
        ::= { lecConfigEntry 3 }

    lecConfigMode OBJECT-TYPE
        SYNTAX      INTEGER {
                             automatic(1),
                             manual(2)
                            }
        MAX-ACCESS  read-create
        STATUS      current
        DESCRIPTION
                "Indicates whether this LAN Emulation Client should
                 auto-configure the next time it is (re)started.

                 In automatic(1) mode, a client uses a LAN Emulation
                 Configuration Server to learn the ATM address of its
                 LAN Emulation Server, and to obtain other parameters.

                 lecConfig{ LanType, MaxDataFrameSize, LanName } are
                 used in the Configure request.  lecConfigLesAtmAddress
                 is ignored.

                 In manual(2) mode, management tells the client the
                 ATM address of its LAN Emulation Server and the
                 values of other parameters.

                 lecConfig{ LanType, MaxDataFrameSize, LanName } are
                 used in the Join request.  lecConfigLesAtmAddress
                 tells the client which LES to call."
        REFERENCE
                "ATM Forum LAN Emulation Over ATM Specification, V1.0,
                 Sections 3.4.1.1 and 5.3"
        DEFVAL   { automatic }
        ::= { lecConfigEntry 4 }

    lecConfigLanType OBJECT-TYPE
        SYNTAX      LecDataFrameFormat
        MAX-ACCESS  read-create
        STATUS      current
        DESCRIPTION
                "C2  LAN Type.

                 The data frame format which this client will use the
                 next time it returns to the Initial State.

                 Auto-configuring clients use this parameter in their
                 Configure requests.  Manually-configured clients use
                 it in their Join requests.

                 This MIB object will not be overwritten with the new
                 value from a LE_{JOIN,CONFIGURE}_RESPONSE.  Instead,
                 lecActualLanType will be."
        REFERENCE
                "ATM Forum LAN Emulation Over ATM Specification, V1.0,
                 Section 5.1.1"
        DEFVAL   { unspecified }
        ::= { lecConfigEntry 5 }

    lecConfigMaxDataFrameSize OBJECT-TYPE
        SYNTAX      LecDataFrameSize
        MAX-ACCESS  read-create
        STATUS      current
        DESCRIPTION
                "C3  Maximum Data Frame Size.

                 The maximum data frame size which this client will
                 use the next time it returns to the Initial State.

                 Auto-configuring clients use this parameter in their
                 Configure requests.  Manually-configured clients use
                 it in their Join requests.

                 This MIB object will not be overwritten with the new
                 value from a LE_{JOIN,CONFIGURE}_RESPONSE.  Instead,
                 lecActualMaxDataFrameSize will be."
        REFERENCE
                "ATM Forum LAN Emulation Over ATM Specification, V1.0,
                 Section 5.1.1"
        DEFVAL   { unspecified }
        ::= { lecConfigEntry 6 }

    lecConfigLanName OBJECT-TYPE
        SYNTAX      DisplayString (SIZE( 0..32 ))
        MAX-ACCESS  read-create
        STATUS      current
        DESCRIPTION
                "C5  ELAN Name.

                 The ELAN Name this client will use the next time it
                 returns to the Initial State.

                 Auto-configuring clients use this parameter in their
                 Configure requests.  Manually-configured clients use
                 it in their Join requests.

                 This MIB object will not be overwritten with the new
                 value from a LE_{JOIN,CONFIGURE}_RESPONSE.  Instead,
                 lecActualLanName will be."
        REFERENCE
                "ATM Forum LAN Emulation Over ATM Specification, V1.0,
                 Section 5.1.1"
        ::= { lecConfigEntry 7 }

    lecConfigLesAtmAddress OBJECT-TYPE
        SYNTAX      AtmLaneAddress
        MAX-ACCESS  read-create
        STATUS      current
        DESCRIPTION
                "C9  LE Server ATM Address.

                 The LAN Emulation Server which this client will use
                 the next time it is started in manual configuration
                 mode.

                 When lecConfigMode is 'automatic', there is no need
                 to set this address, and no advantage to doing so.
                 The client will use the LECS to find a LES, putting
                 the auto-configured address in lecActualLesAtmAddress
                 while leaving lecConfigLesAtmAddress alone."
        REFERENCE
                "ATM Forum LAN Emulation Over ATM Specification, V1.0,
                 Section 5.1.1"
        ::= { lecConfigEntry 8 }

    lecControlTimeout OBJECT-TYPE
        SYNTAX      INTEGER ( 10..300 )
        UNITS       "seconds"
        MAX-ACCESS  read-create
        STATUS      current
        DESCRIPTION
                "C7  Control Time-out.  Time out period used for
                     timing out most request/response control frame
                     interactions, as specified elsewhere [in the
                     LAN Emulation specification].

                 This time value is expressed in seconds."
        REFERENCE
                "ATM Forum LAN Emulation Over ATM Specification, V1.0,
                 Section 5.1.1"
        DEFVAL   { 120 }
        ::= { lecConfigEntry 9 }

    lecMaxUnknownFrameCount OBJECT-TYPE
        SYNTAX      INTEGER ( 1..10 )
        UNITS       "frames"
        MAX-ACCESS  read-create
        STATUS      current
        DESCRIPTION
                "C10 Maximum Unknown Frame Count.  See the description
                     of lecMaxUnknownFrameTime below."
        REFERENCE
                "ATM Forum LAN Emulation Over ATM Specification, V1.0,
                 Section 5.1.1"
        DEFVAL   { 1 }
        ::= { lecConfigEntry 10 }

    lecMaxUnknownFrameTime OBJECT-TYPE
        SYNTAX      INTEGER ( 1..60 )
        UNITS       "seconds"
        MAX-ACCESS  read-create
        STATUS      current
        DESCRIPTION
                "C11 Maximum Unknown Frame Time.  Within the period of
                     time defined by the Maximum Unknown Frame Time, a
                     LE Client will send no more than Maximum Unknown
                     Frame Count frames to the BUS for a given unicast
                     LAN Destination, and it must also initiate the
                     address resolution protocol to resolve that LAN
                     Destination.

                 This time value is expressed in seconds."
        REFERENCE
                "ATM Forum LAN Emulation Over ATM Specification, V1.0,
                 Section 5.1.1"
        DEFVAL   { 1 }
        ::= { lecConfigEntry 11 }

    lecVccTimeoutPeriod OBJECT-TYPE
        SYNTAX      Integer32
        UNITS       "seconds"
        MAX-ACCESS  read-create
        STATUS      current
        DESCRIPTION
                "C12 VCC Time-out Period.  A LE Client SHOULD release
                     any Data Direct VCC that it has not used to
                     transmit or receive any data frames for the
                     length of the VCC Time-out Period.  This parameter
                     is only meaningful for SVC Data Direct VCCs.

                 This time value is expressed in seconds.  The default
                 value is 20 minutes.  A value of 0 seconds means that
                 the timeout period is infinite.  Negative values will
                 be rejected by the agent."
        REFERENCE
                "ATM Forum LAN Emulation Over ATM Specification, V1.0,
                 Section 5.1.1"
        DEFVAL   { 1200 }
        ::= { lecConfigEntry 12 }

    lecMaxRetryCount OBJECT-TYPE
        SYNTAX      INTEGER( 0..2 )
        MAX-ACCESS  read-create
        STATUS      current
        DESCRIPTION
                "C13 Maximum Retry Count.  A LE CLient MUST not retry
                     a LE_ARP_REQUEST for a given frame's LAN
                     destination more than Maximum Retry Count times,
                     after the first LE_ARP_REQUEST for that same
                     frame's LAN destination."
        REFERENCE
                "ATM Forum LAN Emulation Over ATM Specification, V1.0,
                 Section 5.1.1"
        DEFVAL   { 1 }
        ::= { lecConfigEntry 13 }

    lecAgingTime OBJECT-TYPE
        SYNTAX      INTEGER ( 10..300 )
        UNITS       "seconds"
        MAX-ACCESS  read-create
        STATUS      current
        DESCRIPTION
                "C17 Aging Time.  The maximum time that a LE Client
                     will maintain an entry in its LE_ARP cache in
                     the absence of a verification of that
                     relationship.

                 This time value is expressed in seconds."
        REFERENCE
                "ATM Forum LAN Emulation Over ATM Specification, V1.0,
                 Section 5.1.1"
        DEFVAL  { 300 }
        ::= { lecConfigEntry 14 }

    lecForwardDelayTime OBJECT-TYPE
        SYNTAX      INTEGER ( 4..30 )
        UNITS       "seconds"
        MAX-ACCESS  read-create
        STATUS      current
        DESCRIPTION
                "C18 Forward Delay Time.  The maximum time that a LE
                     Client will maintain an entry for a non-local MAC
                     address in its LE_ARP cache in the absence of a
                     verification of that relationship, as long as the
                     Topology Change flag C19 is true.

                 lecForwardDelayTime SHOULD BE less than lecAgingTime.
                 When it is not, lecAgingTime governs LE_ARP aging.

                 This time value is expressed in seconds."
        REFERENCE
                "ATM Forum LAN Emulation Over ATM Specification, V1.0,
                 Section 5.1.1"
        DEFVAL  { 15 }
        ::= { lecConfigEntry 15 }

    lecExpectedArpResponseTime OBJECT-TYPE
        SYNTAX      INTEGER ( 1..30 )
        UNITS       "seconds"
        MAX-ACCESS  read-create
        STATUS      current
        DESCRIPTION
                "C20 Expected LE_ARP Reponse Time.  The maximum time
                     that the LEC expects an LE_ARP_REQUEST/
                     LE_ARP_RESPONSE cycle to take.  Used for retries
                     and verifies.

                 This time value is expressed in seconds."
        REFERENCE
                "ATM Forum LAN Emulation Over ATM Specification, V1.0,
                 Section 5.1.1"
        DEFVAL   { 1 }
        ::= { lecConfigEntry 16 }

    lecFlushTimeOut OBJECT-TYPE
        SYNTAX      INTEGER ( 1..4 )
        UNITS       "seconds"
        MAX-ACCESS  read-create
        STATUS      current
        DESCRIPTION
                "C21 Flush Time-out.  Time limit to wait to receive a
                     LE_FLUSH_RESPONSE after the LE_FLUSH_REQUEST has
                     been sent before taking recovery action.

                 This time value is expressed in seconds."
        REFERENCE
                "ATM Forum LAN Emulation Over ATM Specification, V1.0,
                 Section 5.1.1"
        DEFVAL   { 4 }
        ::= { lecConfigEntry 17 }

    lecPathSwitchingDelay OBJECT-TYPE
        SYNTAX      INTEGER ( 1..8 )
        UNITS       "seconds"
        MAX-ACCESS  read-create
        STATUS      current
        DESCRIPTION
                "C22 Path Switching Delay.  The time since sending a
                     frame to the BUS after which the LE Client may
                     assume that the frame has been either discarded
                     or delivered to the recipient.  May be used to
                     bypass the Flush protocol.

                 This time value is expressed in seconds."
        REFERENCE
                "ATM Forum LAN Emulation Over ATM Specification, V1.0,
                 Section 5.1.1"
        DEFVAL   { 6 }
        ::= { lecConfigEntry 18 }

    lecLocalSegmentID OBJECT-TYPE
        SYNTAX      INTEGER ( 0..4095 )
        MAX-ACCESS  read-create
        STATUS      current
        DESCRIPTION
                "C23 Local Segment ID.  The segment ID of the emulated
                     LAN.  This is only required for IEEE 802.5 clients
                     that are Source Routing bridges."
        REFERENCE
                "ATM Forum LAN Emulation Over ATM Specification, V1.0,
                 Section 5.1.1"
        ::= { lecConfigEntry 19 }

    lecMulticastSendType OBJECT-TYPE
        SYNTAX      INTEGER {
                             bestEffort(1),
                             variableBitRate(2),
                             constantBitRate(3)
                            }
        MAX-ACCESS  read-create
        STATUS      current
        DESCRIPTION
                "C24 Multicast Send VCC Type.  Signalling parameter
                     that SHOULD be used by the LE Client when
                     establishing the Multicast Send VCC.

                     This is the method to be used by the LE Client
                     when specifying traffic parameters when it sets
                     up the Multicast Send VCC for this emulated LAN."
        REFERENCE
                "ATM Forum LAN Emulation Over ATM Specification, V1.0,
                 Section 5.1.1"
        ::= { lecConfigEntry 20 }

    lecMulticastSendAvgRate OBJECT-TYPE
        SYNTAX      Integer32
        UNITS       "cells per second"
        MAX-ACCESS  read-create
        STATUS      current
        DESCRIPTION
                "C25 Multicast Send VCC AvgRate.  Signalling parameter
                     that SHOULD be used by the LE Client when
                     establishing the Multicast Send VCC.

                     Forward and Backward Sustained Cell Rate to be
                     requested by LE Client when setting up Multicast
                     Send VCC, if using Variable bit rate codings."
        REFERENCE
                "ATM Forum LAN Emulation Over ATM Specification, V1.0,
                 Section 5.1.1"
        ::= { lecConfigEntry 21 }

    lecMulticastSendPeakRate OBJECT-TYPE
        SYNTAX      Integer32
        UNITS       "cells per second"
        MAX-ACCESS  read-create
        STATUS      current
        DESCRIPTION
                "C26 Multicast Send VCC PeakRate.  Signalling parameter
                     that SHOULD be used by the LE Client when
                     establishing the Multicast Send VCC.

                     Forward and Backward Peak Cell Rate to be
                     requested by LE Client when setting up the
                     Multicast Send VCC when using either Variable or
                     Constant bit rate codings."
        REFERENCE
                "ATM Forum LAN Emulation Over ATM Specification, V1.0,
                 Section 5.1.1"
        ::= { lecConfigEntry 22 }

    lecConnectionCompleteTimer OBJECT-TYPE
        SYNTAX      INTEGER ( 1..10 )
        UNITS       "seconds"
        MAX-ACCESS  read-create
        STATUS      current
        DESCRIPTION
                "C28 Connection Complete Timer.  Optional.  In
                     Connection Establishment this is the time period
                     in which data or a READY_IND message is expected
                     from a Calling Party.

                 This time value is expressed in seconds."
        REFERENCE
                "ATM Forum LAN Emulation Over ATM Specification, V1.0,
                 Section 5.1.1"
        DEFVAL   { 4 }
        ::= { lecConfigEntry 23 }


    -- ------------------------------------------------------------- --

    --
    --  LAN Emulation Client status group
    --

    lecStatusTable OBJECT-TYPE
        SYNTAX       SEQUENCE OF LecStatusEntry
        MAX-ACCESS   not-accessible
        STATUS       current
        DESCRIPTION
                "A read-only table containing identification, status,
                 and operational information about the LAN Emulation
                 Clients this agent manages."
        ::= { leClientMIBObjects 2 }

    lecStatusEntry OBJECT-TYPE
        SYNTAX       LecStatusEntry
        MAX-ACCESS   not-accessible
        STATUS       current
        DESCRIPTION
                "Each table entry contains information about one LAN
                 Emulation Client."
        AUGMENTS  { lecConfigEntry }
        ::= { lecStatusTable 1 }

    LecStatusEntry ::=
        SEQUENCE {

            --
            --  Client identification
            --
            lecIfIndex                  Integer32,
            lecPrimaryAtmAddress        AtmLaneAddress,
            lecID                       INTEGER,


            --
            --  Client status and protocol version
            --
            lecInterfaceState           LecState,
            lecLastFailureRespCode      INTEGER,
            lecLastFailureState         LecState,
            lecProtocol                 INTEGER,
            lecVersion                  INTEGER,
            lecTopologyChange           TruthValue,


            --
            --  Operational parameters and their source
            --
            lecConfigServerAtmAddress   AtmLaneAddress,
            lecConfigSource             INTEGER,
            lecActualLanType            LecDataFrameFormat,
            lecActualMaxDataFrameSize   LecDataFrameSize,
            lecActualLanName            DisplayString,
            lecActualLesAtmAddress      AtmLaneAddress,
            lecProxyClient              TruthValue

        }

    lecIfIndex OBJECT-TYPE
        SYNTAX      Integer32
        MAX-ACCESS  read-only
        STATUS      current
        DESCRIPTION
                "This object identifies the logical interface number
                 ('ifIndex') assigned to this client, and is used to
                 identify corresponding rows in the Interfaces MIB.

                 Note that re-initialization of the management agent
                 may cause a client's 'lecIfIndex' to change."
        ::= { lecStatusEntry 1 }

    lecPrimaryAtmAddress OBJECT-TYPE
        SYNTAX      AtmLaneAddress
        MAX-ACCESS  read-only
        STATUS      current
        DESCRIPTION
                "C1  LE Client's ATM Addresses.

                 The primary ATM address of this LAN Emulation Client.
                 This address is used to establish the Control Direct
                 and Multicast Send VCCs, and may also be used to set
                 up Data Direct VCCs.

                 A client may have additional ATM addresses for use
                 with Data Direct VCCs.  These addresses are readable
                 via the lecAtmAddressTable."
        REFERENCE
                "ATM Forum LAN Emulation Over ATM Specification, V1.0,
                 Section 5.1.1"
        ::= { lecStatusEntry 2 }

    lecID OBJECT-TYPE
        SYNTAX      INTEGER( 0..65279 )
        MAX-ACCESS  read-only
        STATUS      current
        DESCRIPTION
                "C14 LE Client Identifier.  Each LE Client requires a
                     LE Client Identifier (LECID) assigned by the LE
                     Server during the Join phase.  The LECID is placed
                     in control requests by the LE Client and MAY be
                     used for echo suppression on multicast data frames
                     sent by that LE Client.  This value MUST NOT
                     change without terminating the LE Client and
                     returning to the Initial state.  A valid LECID
                     MUST be in the range X'0001' through X'FEFF'.

                 The value of this object is only meaningful for a LEC
                 that is connected to a LES.  For a LEC which does not
                 belong to an emulated LAN, the value of this object
                 is defined to be 0."
        REFERENCE
                "ATM Forum LAN Emulation Over ATM Specification, V1.0,
                 Section 5.1.1"
        ::= { lecStatusEntry 3 }

    lecInterfaceState OBJECT-TYPE
        SYNTAX      LecState
        MAX-ACCESS  read-only
        STATUS      current
        DESCRIPTION
                "The current state of the LAN Emulation Client.

                 Note that 'ifOperStatus' is defined to be 'up' when,
                 and only when, 'lecInterfaceState' is 'operational'."
        REFERENCE
                "ATM Forum LAN Emulation Over ATM Specification, V1.0,
                 Section 2.3.1"
        ::= { lecStatusEntry 4 }

    lecLastFailureRespCode OBJECT-TYPE
        SYNTAX      INTEGER {
                             none(1),
                             timeout(2),
                             undefinedError(3),
                             versionNotSupported(4),
                             invalidRequestParameters(5),
                             duplicateLanDestination(6),
                             duplicateAtmAddress(7),
                             insufficientResources(8),
                             accessDenied(9),
                             invalidRequesterId(10),
                             invalidLanDestination(11),
                             invalidAtmAddress(12),
                             noConfiguration(13),
                             leConfigureError(14),
                             insufficientInformation(15)
                            }
        MAX-ACCESS  read-only
        STATUS      current
        DESCRIPTION
                "Status code from the last failed Configure response
                 or Join response.  Failed responses are those for
                 which the LE_CONFIGURE_RESPONSE / LE_JOIN_RESPONSE
                 frame contains a non-zero code, or fails to arrive
                 within a timeout period.

                 If none of this client's requests have failed, this
                 object has the value 'none'.

                 If the failed response contained a STATUS code that
                 is not defined in the LAN Emulation specification,
                 this object has the value 'undefinedError'.

                 The value 'timeout' is self-explanatory.

                 Other failure codes correspond to those defined in
                 the specification, although they may have different
                 numeric values."
        REFERENCE
                "ATM Forum LAN Emulation Over ATM Specification, V1.0,
                 Section 4.2, Table 13"
        ::= { lecStatusEntry 5 }

    lecLastFailureState OBJECT-TYPE
        SYNTAX      LecState
        MAX-ACCESS  read-only
        STATUS      current
        DESCRIPTION
                "The state this client was in when it updated the
                 'lecLastFailureRespCode'.

                 If 'lecLastFailureRespCode' is 'none', this object
                 has the value initialState(1)."
        REFERENCE
                "ATM Forum LAN Emulation Over ATM Specification, V1.0,
                 Section 2.3.1"
        ::= { lecStatusEntry 6 }

    lecProtocol OBJECT-TYPE
        SYNTAX      INTEGER ( 1..255 )
        MAX-ACCESS  read-only
        STATUS      current
        DESCRIPTION
                "The LAN Emulation protocol which this client supports,
                 and specifies in its LE_JOIN_REQUESTs."
        REFERENCE
                "ATM Forum LAN Emulation Over ATM Specification, V1.0,
                 Section 4.2"
        ::= { lecStatusEntry 7 }

    lecVersion OBJECT-TYPE
        SYNTAX      INTEGER ( 1..255 )
        MAX-ACCESS  read-only
        STATUS      current
        DESCRIPTION
                "The LAN Emulation protocol version which this client
                 supports, and specifies in its LE_JOIN_REQUESTs."
        REFERENCE
                "ATM Forum LAN Emulation Over ATM Specification, V1.0,
                 Section 4.2"
        ::= { lecStatusEntry 8 }

    lecTopologyChange OBJECT-TYPE
        SYNTAX      TruthValue
        MAX-ACCESS  read-only
        STATUS      current
        DESCRIPTION
                "C19 Topology Change.  Boolean indication that the LE
                     Client is using the Forward Delay Time C18,
                     instead of the Aging Time C17, to age non-local
                     entries in its LE_ARP cache C16.

                 For a client which is not connected to the LES, this
                 object is defined to have the value 'false'."
        REFERENCE
                "ATM Forum LAN Emulation Over ATM Specification, V1.0,
                 Section 5.1.1"
        ::= { lecStatusEntry 9 }

    lecConfigServerAtmAddress OBJECT-TYPE
        SYNTAX      AtmLaneAddress
        MAX-ACCESS  read-only
        STATUS      current
        DESCRIPTION
                "The ATM address of the LAN Emulation Configuration
                 Server (if known) or the empty string (otherwise)."
        ::= { lecStatusEntry 10 }

    lecConfigSource OBJECT-TYPE
        SYNTAX      INTEGER {
                             gotAddressViaIlmi(1),
                             usedWellKnownAddress(2),
                             usedLecsPvc(3),
                             didNotUseLecs(4)
                            }
        MAX-ACCESS  read-only
        STATUS      current
        DESCRIPTION
                "Indicates whether this LAN Emulation Client used the
                 LAN Emulation Configuration Server, and, if so, what
                 method it used to establish the Configuration Direct
                 VCC."
        REFERENCE
                "ATM Forum LAN Emulation Over ATM Specification, V1.0,
                 Section 5.2"
        ::= { lecStatusEntry 11 }


    lecActualLanType OBJECT-TYPE
        SYNTAX      LecDataFrameFormat
        MAX-ACCESS  read-only
        STATUS      current
        DESCRIPTION
                "C2  LAN Type.

                 The data frame format that this LAN Emulation Client
                 is using right now.  This may come from

                     *  lecConfigLanType,
                     *  the LAN Emulation Configuration Server, or
                     *  the LAN Emulation Server

                 This value is related to 'ifMtu' and 'ifType'.  See
                 the LEC management specification for more details."
        REFERENCE
                "ATM Forum LAN Emulation Over ATM Specification, V1.0,
                 Section 5.1.1"
        ::= { lecStatusEntry 12 }

    lecActualMaxDataFrameSize OBJECT-TYPE
        SYNTAX      LecDataFrameSize
        MAX-ACCESS  read-only
        STATUS      current
        DESCRIPTION
                "C3  Maximum Data Frame Size.

                 The maximum data frame size that this LAN Emulation
                 client is using right now.  This may come from

                     *  lecConfigMaxDataFrameSize,
                     *  the LAN Emulation Configuration Server, or
                     *  the LAN Emulation Server                     "
        REFERENCE
                "ATM Forum LAN Emulation Over ATM Specification, V1.0,
                 Section 5.1.1"
        ::= { lecStatusEntry 13 }

    lecActualLanName OBJECT-TYPE
        SYNTAX      DisplayString (SIZE( 0..32 ))
        MAX-ACCESS  read-only
        STATUS      current
        DESCRIPTION
                "C5  ELAN Name.

                 The identity of the emulated LAN which this client
                 last joined, or wishes to join.  This may come from

                     *  lecConfigLanName,
                     *  the LAN Emulation Configuration Server, or
                     *  the LAN Emulation Server                     "
        REFERENCE
                "ATM Forum LAN Emulation Over ATM Specification, V1.0,
                 Section 5.1.1"
        ::= { lecStatusEntry 14 }

    lecActualLesAtmAddress OBJECT-TYPE
        SYNTAX      AtmLaneAddress
        MAX-ACCESS  read-only
        STATUS      current
        DESCRIPTION
                "C9  LE Server ATM Address.

                 The LAN Emulation Server address currently in use or
                 most recently attempted.

                 If no LAN Emulation Server attachment has been tried,
                 this object's value is the zero-length string."
        REFERENCE
                "ATM Forum LAN Emulation Over ATM Specification, V1.0,
                 Section 5.1.1"
        ::= { lecStatusEntry 15 }

    lecProxyClient OBJECT-TYPE
        SYNTAX      TruthValue
        MAX-ACCESS  read-only
        STATUS      current
        DESCRIPTION
                "C4  Proxy.

                 Indicates whether this client is acting as a proxy.

                 Proxy clients are allowed to represent unregistered
                 MAC addresses, and receive copies of LE_ARP_REQUEST
                 frames for such addresses."
        REFERENCE
                "ATM Forum LAN Emulation Over ATM Specification, V1.0,
                 Section 5.1.1"
        ::= { lecStatusEntry 16 }


    -- ------------------------------------------------------------- --

    --
    --  LAN Emulation Client - ifIndex Mapping Table
    --

    lecMappingTable OBJECT-TYPE
        SYNTAX       SEQUENCE OF LecMappingEntry
        MAX-ACCESS   not-accessible
        STATUS       current
        DESCRIPTION
                "A table mapping the 'ifIndex' values of 'aflane8023'
                 and 'aflane8025' interfaces to the 'lecIndex' values
                 of the corresponding LAN Emulation Clients."
        ::= { leClientMIBObjects 3 }

    lecMappingEntry OBJECT-TYPE
        SYNTAX       LecMappingEntry
        MAX-ACCESS   not-accessible
        STATUS       current
        DESCRIPTION
                "Each row describes one ifIndex --> lecIndex mapping."
        INDEX   { ifIndex }
        ::= { lecMappingTable 1 }

    LecMappingEntry ::=
        SEQUENCE {
            lecMappingIndex             INTEGER
        }

    lecMappingIndex OBJECT-TYPE
        SYNTAX      INTEGER ( 1..2147483647 )
        MAX-ACCESS  read-only
        STATUS      current
        DESCRIPTION
                "The 'lecIndex' of the client which implements the
                 specified interface."
        ::= { lecMappingEntry 1 }

    -- ------------------------------------------------------------- --

    --
    --  LAN Emulation Client - Statistics table
    --

    lecStatisticsTable OBJECT-TYPE
        SYNTAX       SEQUENCE OF LecStatisticsEntry
        MAX-ACCESS   not-accessible
        STATUS       current
        DESCRIPTION
                "An extension table containing traffic statistics for
                 all the LAN Emulation Clients this host implements."
        ::= { leClientMIBObjects 4 }

    lecStatisticsEntry OBJECT-TYPE
        SYNTAX       LecStatisticsEntry
        MAX-ACCESS   not-accessible
        STATUS       current
        DESCRIPTION
                "Each row in this table contains traffic statistics
                 for one LAN Emulation client."
        AUGMENTS  { lecConfigEntry }
        ::= { lecStatisticsTable 1 }

    LecStatisticsEntry ::=
        SEQUENCE {
            lecArpRequestsOut           Counter32,
            lecArpRequestsIn            Counter32,
            lecArpRepliesOut            Counter32,
            lecArpRepliesIn             Counter32,
            lecControlFramesOut         Counter32,
            lecControlFramesIn          Counter32,
            lecSvcFailures              Counter32
        }

    lecArpRequestsOut OBJECT-TYPE
        SYNTAX      Counter32
        MAX-ACCESS  read-only
        STATUS      current
        DESCRIPTION
                "The number of LE_ARP_REQUESTs sent over the LUNI by
                 this LAN Emulation Client."
        ::= { lecStatisticsEntry 1 }

    lecArpRequestsIn OBJECT-TYPE
        SYNTAX      Counter32
        MAX-ACCESS  read-only
        STATUS      current
        DESCRIPTION
                "The number of LE_ARP_REQUESTs received over the LUNI
                 by this LAN Emulation Client.

                 Requests may arrive on the Control Direct VCC or on
                 the Control Distribute VCC, depending upon how the
                 LES is implemented and the chances it has had for
                 learning.  This counter covers both VCCs."
        ::= { lecStatisticsEntry 2 }

    lecArpRepliesOut OBJECT-TYPE
        SYNTAX      Counter32
        MAX-ACCESS  read-only
        STATUS      current
        DESCRIPTION
                "The number of LE_ARP_RESPONSEs sent over the LUNI by
                 this LAN Emulation Client."
        ::= { lecStatisticsEntry 3 }

    lecArpRepliesIn OBJECT-TYPE
        SYNTAX      Counter32
        MAX-ACCESS  read-only
        STATUS      current
        DESCRIPTION
                "The number of LE_ARP_RESPONSEs received over the LUNI
                 by this LAN Emulation Client.  This count includes
                 all such replies, whether solicited or not.

                 Replies may arrive on the Control Direct VCC or on
                 the Control Distribute VCC, depending upon how the
                 LES is implemented.  This counter covers both VCCs."
        ::= { lecStatisticsEntry 4 }

    lecControlFramesOut OBJECT-TYPE
        SYNTAX      Counter32
        MAX-ACCESS  read-only
        STATUS      current
        DESCRIPTION
                "The total number of control packets sent by this
                 LAN Emulation Client over the LUNI."
        ::= { lecStatisticsEntry 5 }

    lecControlFramesIn OBJECT-TYPE
        SYNTAX      Counter32
        MAX-ACCESS  read-only
        STATUS      current
        DESCRIPTION
                "The total number of control packets received by this
                 LAN Emulation Client over the LUNI."
        ::= { lecStatisticsEntry 6 }

    lecSvcFailures OBJECT-TYPE
        SYNTAX      Counter32
        MAX-ACCESS  read-only
        STATUS      current
        DESCRIPTION
                "The total number of

                     *  outgoing LAN Emulation SVCs which this client
                        tried, but failed, to open;

                     *  incoming LAN Emulation SVCs which this client
                        tried, but failed to establish; and

                     *  incoming LAN Emulation SVCs which this client
                        rejected for protocol or security reasons.   "
        ::= { lecStatisticsEntry 7 }

    -- ------------------------------------------------------------- --

    --
    --  LAN Emulation Client - Server VCC table
    --

    lecServerVccTable OBJECT-TYPE
        SYNTAX       SEQUENCE OF LecServerVccEntry
        MAX-ACCESS   not-accessible
        STATUS       current
        DESCRIPTION
                "A table identifying the Control and Multicast VCCs
                 for each LAN Emulation Client this host implements."
        ::= { leClientMIBObjects 5 }

    lecServerVccEntry OBJECT-TYPE
        SYNTAX       LecServerVccEntry
        MAX-ACCESS   not-accessible
        STATUS       current
        DESCRIPTION
                "Each row in this table describes the Control VCCs
                 and Multicast VCCs for one LAN Emulation client."
        AUGMENTS  { lecConfigEntry }
        ::= { lecServerVccTable 1 }

    LecServerVccEntry ::=
        SEQUENCE {

    --
    --  Note that the 'lec*Interface' objects double as 'connection
    --  exists' flags.
    --
            lecConfigDirectInterface       LeConnectionInterface,
            lecConfigDirectVpi             VpiInteger,
            lecConfigDirectVci             VciInteger,

            lecControlDirectInterface      LeConnectionInterface,
            lecControlDirectVpi            VpiInteger,
            lecControlDirectVci            VciInteger,

            lecControlDistributeInterface  LeConnectionInterface,
            lecControlDistributeVpi        VpiInteger,
            lecControlDistributeVci        VciInteger,

            lecMulticastSendInterface      LeConnectionInterface,
            lecMulticastSendVpi            VpiInteger,
            lecMulticastSendVci            VciInteger,

            lecMulticastForwardInterface   LeConnectionInterface,
            lecMulticastForwardVpi         VpiInteger,
            lecMulticastForwardVci         VciInteger
        }

    lecConfigDirectInterface OBJECT-TYPE
        SYNTAX      LeConnectionInterface
        MAX-ACCESS  read-only
        STATUS      current
        DESCRIPTION
                "The interface associated with the Configuration
                 Direct VCC.  If no Configuration Direct VCC exists,
                 this object has the value 0.  Otherwise, the objects

                     ( lecConfigDirectInterface,
                       lecConfigDirectVpi, lecConfigDirectVci )

                 identify the circuit."
        REFERENCE
              "ATM Forum LAN Emulation Over ATM Specification, V1.0,
               Section 2.2.2.1.1"
        ::= { lecServerVccEntry 1 }

    lecConfigDirectVpi OBJECT-TYPE
        SYNTAX      VpiInteger
        MAX-ACCESS  read-only
        STATUS      current
        DESCRIPTION
                "If the Configuration Direct VCC exists, this object
                 contains the VPI which identifies that VCC at
                 the point where it connects to this LE client.

                 Otherwise, this object has the value 0."
        REFERENCE
              "ATM Forum LAN Emulation Over ATM Specification, V1.0,
               Section 2.2.2.1.1"
        ::= { lecServerVccEntry 2 }

    lecConfigDirectVci OBJECT-TYPE
        SYNTAX      VciInteger
        MAX-ACCESS  read-only
        STATUS      current
        DESCRIPTION
                "If the Configuration Direct VCC exists, this object
                 contains the VCI which identifies that VCC at
                 the point where it connects to this LE client.

                 Otherwise, this object has the value 0."
        REFERENCE
              "ATM Forum LAN Emulation Over ATM Specification, V1.0,
               Section 2.2.2.1.1"
        ::= { lecServerVccEntry 3 }

    lecControlDirectInterface OBJECT-TYPE
        SYNTAX      LeConnectionInterface
        MAX-ACCESS  read-only
        STATUS      current
        DESCRIPTION
                "The interface associated with the Control Direct VCC.
                 If no Control Direct VCC exists, this object has the
                 value 0.  Otherwise, the objects

                     ( lecControlDirectInterface,
                       lecControlDirectVpi, lecControlDirectVci )

                 identify the circuit."
        REFERENCE
              "ATM Forum LAN Emulation Over ATM Specification, V1.0,
               Section 2.2.2.1.2"
        ::= { lecServerVccEntry 4 }

    lecControlDirectVpi OBJECT-TYPE
        SYNTAX      VpiInteger
        MAX-ACCESS  read-only
        STATUS      current
        DESCRIPTION
                "If the Control Direct VCC exists, this object
                 contains the VPI which identifies that VCC at
                 the point where it connects to this LE client.

                 Otherwise, this object has the value 0."
        REFERENCE
              "ATM Forum LAN Emulation Over ATM Specification, V1.0,
               Section 2.2.2.1.2"
        ::= { lecServerVccEntry 5 }

    lecControlDirectVci OBJECT-TYPE
        SYNTAX      VciInteger
        MAX-ACCESS  read-only
        STATUS      current
        DESCRIPTION
                "If the Control Direct VCC exists, this object
                 contains the VCI which identifies that VCC at
                 the point where it connects to this LE client.

                 Otherwise, this object has the value 0."
        REFERENCE
              "ATM Forum LAN Emulation Over ATM Specification, V1.0,
               Section 2.2.2.1.2"
        ::= { lecServerVccEntry 6 }

    lecControlDistributeInterface OBJECT-TYPE
        SYNTAX      LeConnectionInterface
        MAX-ACCESS  read-only
        STATUS      current
        DESCRIPTION
                "The interface associated with the Control Distribute
                 VCC.  If no Control Distribute VCC has been set up to
                 this client, this object has the value 0.  Otherwise,
                 the objects

                     ( lecControlDistributeInterface,
                       lecControlDistributeVpi,
                       lecControlDistributeVci )

                 identify the circuit."
        REFERENCE
              "ATM Forum LAN Emulation Over ATM Specification, V1.0,
               Section 2.2.2.1.3"
        ::= { lecServerVccEntry 7 }

    lecControlDistributeVpi OBJECT-TYPE
        SYNTAX      VpiInteger
        MAX-ACCESS  read-only
        STATUS      current
        DESCRIPTION
                "If the Control Distribute VCC exists, this object
                 contains the VPI which identifies that VCC at the
                 point where it connects to this LE client.

                 Otherwise, this object has the value 0."
        REFERENCE
              "ATM Forum LAN Emulation Over ATM Specification, V1.0,
               Section 2.2.2.1.3"
        ::= { lecServerVccEntry 8 }

    lecControlDistributeVci OBJECT-TYPE
        SYNTAX      VciInteger
        MAX-ACCESS  read-only
        STATUS      current
        DESCRIPTION
                "If the Control Distribute VCC exists, this object
                 contains the VCI which identifies that VCC at the
                 point where it connects to this LE client.

                 Otherwise, this object contains the value 0."
        REFERENCE
              "ATM Forum LAN Emulation Over ATM Specification, V1.0,
               Section 2.2.2.1.3"
        ::= { lecServerVccEntry 9 }

    lecMulticastSendInterface OBJECT-TYPE
        SYNTAX      LeConnectionInterface
        MAX-ACCESS  read-only
        STATUS      current
        DESCRIPTION
                "The interface associated with the Multicast Send
                 VCC.  If no Multicast Send VCC exists, this object
                 has the value 0.  Otherwise, the objects

                     ( lecMulticastSendInterface,
                       lecMulticastSendVpi, lecMulticastSendVci )

                 identify the circuit."
        REFERENCE
              "ATM Forum LAN Emulation Over ATM Specification, V1.0,
               Section 2.2.2.2.2"
        ::= { lecServerVccEntry 10 }

    lecMulticastSendVpi OBJECT-TYPE
        SYNTAX      VpiInteger
        MAX-ACCESS  read-only
        STATUS      current
        DESCRIPTION
                "If the Multicast Send VCC exists, this object
                 contains the VPI which identifies that VCC at
                 the point where it connects to this LE client.

                 Otherwise, this object has the value 0."
        REFERENCE
              "ATM Forum LAN Emulation Over ATM Specification, V1.0,
               Section 2.2.2.2.2"
        ::= { lecServerVccEntry 11 }

    lecMulticastSendVci OBJECT-TYPE
        SYNTAX      VciInteger
        MAX-ACCESS  read-only
        STATUS      current
        DESCRIPTION
                "If the Multicast Send VCC exists, this object
                 contains the VCI which identifies that VCC at
                 the point where it connects to this LE client.

                 Otherwise, this object has the value 0."
        REFERENCE
              "ATM Forum LAN Emulation Over ATM Specification, V1.0,
               Section 2.2.2.2.2"
        ::= { lecServerVccEntry 12 }

    lecMulticastForwardInterface OBJECT-TYPE
        SYNTAX      LeConnectionInterface
        MAX-ACCESS  read-only
        STATUS      current
        DESCRIPTION
                "The interface associated with the Multicast Forward
                 VCC.  If no Multicast Forward VCC has been set up to
                 this client, this object has the value 0.  Otherwise,
                 the objects

                     ( lecMulticastForwardInterface,
                       lecMulticastForwardVpi,
                       lecMulticastForwardVci )

                 identify the circuit."
        REFERENCE
              "ATM Forum LAN Emulation Over ATM Specification, V1.0,
               Section 2.2.2.2.3"
        ::= { lecServerVccEntry 13 }

    lecMulticastForwardVpi OBJECT-TYPE
        SYNTAX      VpiInteger
        MAX-ACCESS  read-only
        STATUS      current
        DESCRIPTION
                "If the Multicast Forward VCC exists, this object
                 contains the VPI which identifies that VCC at the
                 point where it connects to this LE client.

                 Otherwise, this object has the value 0."
        REFERENCE
              "ATM Forum LAN Emulation Over ATM Specification, V1.0,
               Section 2.2.2.2.3"
        ::= { lecServerVccEntry 14 }

    lecMulticastForwardVci OBJECT-TYPE
        SYNTAX      VciInteger
        MAX-ACCESS  read-only
        STATUS      current
        DESCRIPTION
                "If the Multicast Forward VCC exists, this object
                 contains the VCI which identifies that VCC at the
                 point where it connects to this LE client.

                 Otherwise, this object has the value 0."
        REFERENCE
              "ATM Forum LAN Emulation Over ATM Specification, V1.0,
               Section 2.2.2.2.3"
        ::= { lecServerVccEntry 15 }

    -- ------------------------------------------------------------- --

    --
    --  LAN Emulation Client - ATM Addresses table
    --

    lecAtmAddressTable OBJECT-TYPE
        SYNTAX       SEQUENCE OF LecAtmAddressEntry
        MAX-ACCESS   not-accessible
        STATUS       current
        DESCRIPTION
                "A table listing all of the ATM addresses belonging
                 to this host's LAN Emulation Clients."
        ::= { leClientMIBObjects 6 }

    lecAtmAddressEntry OBJECT-TYPE
        SYNTAX       LecAtmAddressEntry
        MAX-ACCESS   not-accessible
        STATUS       current
        DESCRIPTION
                "Each row in this table describes one of a client's
                 ATM addresses."
        INDEX   { lecIndex, lecAtmAddress }
        ::= { lecAtmAddressTable 1 }

    LecAtmAddressEntry ::=
        SEQUENCE {
            lecAtmAddress               AtmLaneAddress,
            lecAtmAddressStatus         RowStatus
        }

    lecAtmAddress OBJECT-TYPE
        SYNTAX      AtmLaneAddress
        MAX-ACCESS  not-accessible
        STATUS      current
        DESCRIPTION
                "The ATM address this row describes.  This could be
                 either a primary address or a secondary address."
        ::= { lecAtmAddressEntry 1 }

    lecAtmAddressStatus OBJECT-TYPE
        SYNTAX      RowStatus
        MAX-ACCESS  read-create
        STATUS      current
        DESCRIPTION
                "Used to create and delete rows in this table.

                 A management station may not change the status of a
                 primary ATM address to 'notInService' or 'destroy'
                 unless the client's ifAdminStatus is 'down', and the
                 client's lecInterfaceState is 'initialState'.

                 Secondary ATM addresses may be destroyed at any time
                 permitted by the agent."
        ::= { lecAtmAddressEntry 2 }


    -- ------------------------------------------------------------- --

    --
    --  LAN Emulation Client Registered MAC Addresses group
    --

    lecMacAddressTable OBJECT-TYPE
        SYNTAX      SEQUENCE OF LecMacAddressEntry
        MAX-ACCESS  not-accessible
        STATUS      current
        DESCRIPTION
                "This table contains entries for all of the registered
                 MAC addresses belonging to this agent's LE clients.

                 C6  Local Unicast MAC Address(es).  Each LE Client has
                     zero or more local unicast MAC addresses.  In an
                     operational LE Client, every address in this
                     variable MUST have been registered with the LE
                     Server.  Two LE CLients joined to the same
                     emulated LAN MUST NOT have the same local unicast
                     MAC address.  A LE Client's MAC addresses may
                     change during normal operations.  When answering
                     a LE_ARP_REQUEST for any address in this list, the
                     'Remote Address' bit in the FLAGS field of the
                     LE_ARP_RESPONSE MUST be clear."
        REFERENCE
                "ATM Forum LAN Emulation Over ATM Specification, V1.0,
                 Section 5.1.1"
        ::= { leClientMIBObjects 7 }

    lecMacAddressEntry OBJECT-TYPE
        SYNTAX      LecMacAddressEntry
        MAX-ACCESS  not-accessible
        STATUS      current
        DESCRIPTION
                "Each table row describes a (MAC address, ATM address)
                 pair registered for a particular client."
        INDEX   { lecIndex, lecMacAddress }
        ::= { lecMacAddressTable 1 }

    LecMacAddressEntry ::=
        SEQUENCE {
            lecMacAddress              MacAddress,
            lecMacAddressAtmBinding    AtmLaneAddress
        }

    lecMacAddress OBJECT-TYPE
        SYNTAX      MacAddress
        MAX-ACCESS  not-accessible
        STATUS      current
        DESCRIPTION
                "A unicast MAC address which the LE client denoted by
                 'lecIndex' has registered with its LE Server."
        ::= { lecMacAddressEntry 1 }

    lecMacAddressAtmBinding OBJECT-TYPE
        SYNTAX      AtmLaneAddress
        MAX-ACCESS  read-only
        STATUS      current
        DESCRIPTION
                "The ATM address registered for 'lecMacAddress'."
        ::= { lecMacAddressEntry 2 }


    -- ------------------------------------------------------------- --

    --
    --  LAN Emulation Client Registered Route Descriptors group
    --

    lecRouteDescrTable OBJECT-TYPE
        SYNTAX      SEQUENCE OF LecRouteDescrEntry
        MAX-ACCESS  not-accessible
        STATUS      current
        DESCRIPTION
                "This table lists all of the Route Descriptors which
                 are registered by this host's LAN Emulation Clients.

                 C8  Route Descriptor(s).  Route Descriptors exist only
                     for source-routed IEEE 802.5 LE Clients that are
                     Source-Route Bridges.  All Route Descriptors in
                     any given emulated LAN MUST be unique.  A LE
                     Client MAY have zero or more Route Descriptors
                     and these Route Descriptors MAY change during
                     normal operation.  In an operational LE Client,
                     every Local Route Descriptor in C8 MUST have been
                     registered with the LE Server.  When answering a
                     LE_ARP_REQUEST for any address in this list, the
                     'Remote Address' bit in the FLAGS field of the
                     LE_ARP_RESPONSE MUST be clear."
        REFERENCE
                "ATM Forum LAN Emulation Over ATM Specification, V1.0,
                 Section 5.1.1"
        ::= { leClientMIBObjects 8 }

    lecRouteDescrEntry OBJECT-TYPE
        SYNTAX      LecRouteDescrEntry
        MAX-ACCESS  not-accessible
        STATUS      current
        DESCRIPTION
                "Each table row describes a (Route Descriptor, ATM
                 address) pair registered for a particular client."
        INDEX   { lecIndex, lecRouteDescrSegmentID,
                            lecRouteDescrBridgeNumber }
        ::= { lecRouteDescrTable 1 }

    LecRouteDescrEntry ::=
        SEQUENCE {
            lecRouteDescrSegmentID     INTEGER,
            lecRouteDescrBridgeNumber  INTEGER,
            lecRouteDescrAtmBinding    AtmLaneAddress
        }

    lecRouteDescrSegmentID OBJECT-TYPE
        SYNTAX      INTEGER( 0..4095 )
        MAX-ACCESS  not-accessible
        STATUS      current
        DESCRIPTION
                "The LAN ID portion of the IEEE 802.5 route descriptor
                 associated with this conceptual row."
        ::= { lecRouteDescrEntry 1 }

    lecRouteDescrBridgeNumber OBJECT-TYPE
        SYNTAX      INTEGER( 0..15 )
        MAX-ACCESS  not-accessible
        STATUS      current
        DESCRIPTION
                "The Bridge Number portion of the IEEE 802.5 route
                 descriptor associated with this conceptual row."
        ::= { lecRouteDescrEntry 2 }

    lecRouteDescrAtmBinding OBJECT-TYPE
        SYNTAX      AtmLaneAddress
        MAX-ACCESS  read-only
        STATUS      current
        DESCRIPTION
                "The ATM address registered for the IEEE 802.5 route
                 descriptor ('lecRouteDescrSegmentID',
                 'lecRouteDescrBridgeNumber')."
        ::= { lecRouteDescrEntry 3 }

    -- ------------------------------------------------------------- --

    --
    --  LAN Emulation Client ARP cache group - MAC addresses
    --

    leArpTable OBJECT-TYPE
        SYNTAX      SEQUENCE OF LeArpEntry
        MAX-ACCESS  not-accessible
        STATUS      current
        DESCRIPTION
                "This table provides access to an ATM LAN Emulation
                 Client's MAC-to-ATM ARP cache.  It contains entries
                 for unicast addresses and for the broadcast address,
                 but not for multicast MAC addresses.

                 C16 LE_ARP Cache.  A table of entries, each of which
                     establishes a relationship between a LAN
                     Destination external to the LE Client and the
                     ATM address to which data frames for that LAN
                     Destination will be sent."
        REFERENCE
                "ATM Forum LAN Emulation Over ATM Specification,
                 Section 5.1.1"
        ::= { leClientMIBObjects 9 }

    leArpEntry OBJECT-TYPE
        SYNTAX      LeArpEntry
        MAX-ACCESS  not-accessible
        STATUS      current
        DESCRIPTION
                "An ATM LAN Emulation ARP cache entry containing
                 information about the binding of one MAC address
                 to one ATM address."
        INDEX   { lecIndex, leArpMacAddress }
        ::= { leArpTable 1 }

    LeArpEntry ::=
        SEQUENCE {
            leArpMacAddress             MacAddress,
            leArpAtmAddress             AtmLaneAddress,
            leArpIsRemoteAddress        TruthValue,
            leArpEntryType              LeArpTableEntryType,
            leArpRowStatus              RowStatus
        }

    leArpMacAddress OBJECT-TYPE
        SYNTAX      MacAddress
        MAX-ACCESS  not-accessible
        STATUS      current
        DESCRIPTION
                "The MAC address for which this cache entry provides
                 a translation.  Since ATM LAN Emulation uses an ARP
                 protocol to locate the Broadcast and Unknown Server,
                 the value of this object could be the broadcast MAC
                 address.

                 MAC addresses should be unique within any given ATM
                 Emulated LAN.  However, there's no requirement that
                 they be unique across disjoint emulated LANs."
        ::= { leArpEntry 1 }

    leArpAtmAddress OBJECT-TYPE
        SYNTAX      AtmLaneAddress
        MAX-ACCESS  read-create
        STATUS      current
        DESCRIPTION
                "The ATM address of the Broadcast & Unknown Server
                 or LAN Emulation Client whose MAC address is stored
                 in 'leArpMacAddress'.

                 This value may be determined through the use of the
                 LE_ARP procedure, through source address learning,
                 or through other mechanisms.

                 Some agents may provide write access to this object,
                 as part of their support for 'static' LE_ARP entries.
                 The effect of attempting to write an ATM address to
                 a 'learned' row is explicitly undefined.  Agents may
                 disallow the write, accept the write and change the
                 row's type, or even accept the write as-is."
        ::= { leArpEntry 2 }

    leArpIsRemoteAddress OBJECT-TYPE
        SYNTAX      TruthValue
        MAX-ACCESS  read-only
        STATUS      current
        DESCRIPTION
                "Indicates whether this entry is for a local or remote
                 MAC address.

                 In this context, 'local' means 'a MAC address that is
                 local to the remote client', as opposed to 'one of my
                 addresses'.

                     true(1)
                         The address is believed to be remote - or its
                         local/remote status is unknown.

                         For an entry created via the LE_ARP mechanism,
                         this corresponds to the 'Remote address' flag
                         being set in the LE_ARP_RESPONSE.

                         During Topology Change periods, remote LE_ARP
                         entries generally age out faster than others.
                         Specifically, they are subject to the Forward
                         Delay Time as well as to the Aging Time.

                     false(2)
                         The address is believed to be local - that is
                         to say, registered with the LES by the client
                         whose ATM address is leArpAtmAddress.

                         For an entry created via the LE_ARP mechanism,
                         this corresponds to the 'Remote address' flag
                         being cleared in the LE_ARP_RESPONSE."
        ::= { leArpEntry 3 }

    leArpEntryType OBJECT-TYPE
        SYNTAX      LeArpTableEntryType
        MAX-ACCESS  read-create
        STATUS      current
        DESCRIPTION
                "Indicates how this LE_ARP table entry was created and
                 whether it is aged."
        DEFVAL   { staticVolatile }
        ::= { leArpEntry 4 }

    leArpRowStatus OBJECT-TYPE
        SYNTAX      RowStatus
        MAX-ACCESS  read-create
        STATUS      current
        DESCRIPTION
                "Lets users create and delete LE_ARP cache entries,
                 on systems that support this capability.

                 Normally clients will maintain their LE_ARP caches
                 automatically.  However, managers may occasionally
                 want to create 'static' LE_ARP cache entries.

                 Rules

                   1.  Before a new row can become 'active', values
                       must be supplied for the columnar objects
                       leArpAtmAddress and leArpEntryType.

                   2.  It is not necessary to set leArpRowStatus to
                       'notInService' in order to modify a writable
                       object in the same conceptual row.

                   3.  LE_ARP entries whose status is 'notReady' or
                       'notInService' will not be used to translate
                       LAN Destinations to ATM Addresses.  However,
                       clients may overwrite such entries with data
                       obtained from other sources.  For example, a
                       client which needed to transmit a data frame
                       to a given MAC address (or via a given Route
                       Descriptor) might find that its LE_ARP entry
                       for the LAN Destination is 'notInService' or
                       'notReady'.  The client might then act as if
                       the LAN Destination was unknown - generating
                       a LE_ARP_REQUEST, flooding the data frame to
                       the BUS, and creating a new, 'active' LE_ARP
                       cache entry based on the LE_ARP_RESPONSE."
        ::= { leArpEntry 5 }

    -- ------------------------------------------------------------- --

    --
    --  LAN Emulation Client ARP cache group - Route Descriptors
    --

    leRDArpTable OBJECT-TYPE
        SYNTAX      SEQUENCE OF LeRDArpEntry
        MAX-ACCESS  not-accessible
        STATUS      current
        DESCRIPTION
                "This table provides access to an ATM LAN Emulation
                 Client's Route Descriptor-to-ATM ARP cache.

                 Implementation of this table is optional for hosts
                 that do not support emulated IEEE 802.5 Token Ring
                 LANs, and mandatory for hosts which do.

                 C16 LE_ARP Cache.  A table of entries, each of which
                     establishes a relationship between a LAN
                     Destination external to the LE Client and the
                     ATM address to which data frames for that LAN
                     Destination will be sent."
        REFERENCE
                "ATM Forum LAN Emulation Over ATM Specification,
                 Section 5.1.1"
        ::= { leClientMIBObjects 10 }

    leRDArpEntry OBJECT-TYPE
        SYNTAX      LeRDArpEntry
        MAX-ACCESS  not-accessible
        STATUS      current
        DESCRIPTION
                "An ATM LAN Emulation ARP cache entry containing
                 information about the binding of one IEEE 802.5
                 route descriptor to one ATM address."
        INDEX   { lecIndex, leRDArpSegmentID, leRDArpBridgeNumber }
        ::= { leRDArpTable 1 }

    LeRDArpEntry ::=
        SEQUENCE {
            leRDArpSegmentID              INTEGER,
            leRDArpBridgeNumber           INTEGER,
            leRDArpAtmAddress             AtmLaneAddress,
            leRDArpEntryType              LeArpTableEntryType,
            leRDArpRowStatus              RowStatus
        }

    leRDArpSegmentID OBJECT-TYPE
        SYNTAX      INTEGER ( 0..4095 )
        MAX-ACCESS  not-accessible
        STATUS      current
        DESCRIPTION
                "The LAN ID portion of the IEEE 802.5 route descriptor
                 associated with this ARP cache entry."
        ::= { leRDArpEntry 1 }

    leRDArpBridgeNumber OBJECT-TYPE
        SYNTAX      INTEGER ( 0..15 )
        MAX-ACCESS  not-accessible
        STATUS      current
        DESCRIPTION
                "The Bridge Number portion of the IEEE 802.5 route
                 descriptor associated with this ARP cache entry."
        ::= { leRDArpEntry 2 }

    leRDArpAtmAddress OBJECT-TYPE
        SYNTAX      AtmLaneAddress
        MAX-ACCESS  read-create
        STATUS      current
        DESCRIPTION
                "The ATM address of the LAN Emulation Client which is
                 associated with the route descriptor
                 ('leRDArpSegmentID', 'leRDArpBridgeNumber').

                 This value may be determined through the use of the
                 LE_ARP procedure, through source address learning,
                 or through other mechanisms.

                 Some agents may provide write access to this object,
                 as part of their support for 'static' LE_ARP entries.
                 The effect of attempting to write an ATM address to
                 a 'learned' row is explicitly undefined.  Agents may
                 disallow the write, accept the write and change the
                 row's type, or even accept the write as-is."
        ::= { leRDArpEntry 3 }

    leRDArpEntryType OBJECT-TYPE
        SYNTAX      LeArpTableEntryType
        MAX-ACCESS  read-create
        STATUS      current
        DESCRIPTION
                "Indicates how this LE_ARP table entry was created and
                 whether it is aged."
        DEFVAL   { staticVolatile }
        ::= { leRDArpEntry 4 }

    leRDArpRowStatus OBJECT-TYPE
        SYNTAX      RowStatus
        MAX-ACCESS  read-create
        STATUS      current
        DESCRIPTION
                "Lets users create and delete LE_ARP cache entries,
                 on systems that support this capability.

                 Normally clients will maintain their LE_ARP caches
                 automatically.  However, managers may occasionally
                 want to create 'static' LE_ARP cache entries.

                 Rules

                   1.  Before a new row can become 'active', values
                       must be supplied for the columnar objects
                       leRDArpAtmAddress and leRDArpEntryType.

                   2.  It is not necessary to set leRDArpRowStatus to
                       'notInService' in order to modify a writable
                       object in the same conceptual row.

                   3.  LE_ARP entries whose status is 'notReady' or
                       'notInService' will not be used to translate
                       LAN Destinations to ATM Addresses.  However,
                       clients may overwrite such entries with data
                       obtained from other sources.  For example, a
                       client which needed to transmit a data frame
                       to a given MAC address (or via a given Route
                       Descriptor) might find that its LE_ARP entry
                       for the LAN Destination is 'notInService' or
                       'notReady'.  The client might then act as if
                       the LAN Destination was unknown - generating
                       a LE_ARP_REQUEST, flooding the data frame to
                       the BUS, and creating a new, 'active' LE_ARP
                       cache entry based on the LE_ARP_RESPONSE."
        ::= { leRDArpEntry 5 }


-- Conformance Information

leClientMIBConformance  OBJECT IDENTIFIER ::= { leClientMIB 2 }

leClientMIBGroups       OBJECT IDENTIFIER ::=
                                           { leClientMIBConformance 1 }
leClientMIBCompliances  OBJECT IDENTIFIER ::= 
                                           { leClientMIBConformance 2 }

-- Compliance Statements

leClientMIBCompliance           MODULE-COMPLIANCE
        STATUS           current
        DESCRIPTION     "The compliance statement for SNMP entities
                         which support ATM LAN Emulation Clients.

        For a host to conform to this MIB, it must also implement

          - RFC 1213 - MIB II.

          - Interfaces table entries for each LE Client, as per the
            LAN Emulation Client management specification.

          - The AToM MIB (RFC 1695 - Definitions of Managed Objects
            for ATM Management), according to the conformance
            statements defined in that RFC.

        Optionally, a host may implement

          - RFC 1573 - Evolution of the Interfaces Group of MIB-II.

          - The 'ifRcvAddressGroup' from RFC 1573, which provides a
            way to represent and configure interfaces with multiple
            addresses.

        See the LAN Emulation Client management specification for
        interpretations of RFC 1573 / MIB-II as they apply to LAN
        Emulation Clients."


        MODULE -- this module
            MANDATORY-GROUPS   {leClientConfigGroup,
                                leClientStatusGroup,
                                leClientMappingGroup,
                                leClientStatisticsGroup,
                                leClientServerVccGroup,
                                leClientAtmAddressesGroup,
                                leClientMacAddressesGroup,
                                leClientArpGroup}

            GROUP               leClientRouteDescriptorsGroup
            DESCRIPTION         "This group is mandatory only for hosts
                                 that support emulated 802.5 LANs."

            GROUP               leClientRDArpGroup
            DESCRIPTION         "This group is mandatory only for hosts
                                 that support emulated 802.5 LANs."

            OBJECT              lecRowStatus
            MIN-ACCESS          read-only
            DESCRIPTION         "Write access is not required."

            OBJECT              lecOwner
            MIN-ACCESS          read-only
            DESCRIPTION         "Write access is not required."

            OBJECT              lecConfigMode
            MIN-ACCESS          read-only
            DESCRIPTION         "Write access is not required."

            OBJECT              lecConfigLanType
            MIN-ACCESS          read-only
            DESCRIPTION         "Write access is not required.

                                 Implementations are not required to
                                 support all legal values."

            OBJECT              lecConfigMaxDataFrameSize
            MIN-ACCESS          read-only
            DESCRIPTION         "Write access is not required.

                                 Implementations are not required to
                                 support all legal values."

            OBJECT              lecConfigLanName
            MIN-ACCESS          read-only
            DESCRIPTION         "Write access is not required."

            OBJECT              lecConfigLesAtmAddress
            MIN-ACCESS          read-only
            DESCRIPTION         "Write access is not required."

            OBJECT              lecControlTimeout
            MIN-ACCESS          read-only
            DESCRIPTION         "Write access is not required."

            OBJECT              lecMaxUnknownFrameCount
            MIN-ACCESS          read-only
            DESCRIPTION         "Write access is not required."

            OBJECT              lecMaxUnknownFrameTime
            MIN-ACCESS          read-only
            DESCRIPTION         "Write access is not required."

            OBJECT              lecVccTimeoutPeriod
            MIN-ACCESS          read-only
            DESCRIPTION         "Write access is not required."

            OBJECT              lecMaxRetryCount
            MIN-ACCESS          read-only
            DESCRIPTION         "Write access is not required."

            OBJECT              lecAgingTime
            MIN-ACCESS          read-only
            DESCRIPTION         "Write access is not required."

            OBJECT              lecForwardDelayTime
            MIN-ACCESS          read-only
            DESCRIPTION         "Write access is not required."

            OBJECT              lecExpectedArpResponseTime
            MIN-ACCESS          read-only
            DESCRIPTION         "Write access is not required."

            OBJECT              lecFlushTimeOut
            MIN-ACCESS          read-only
            DESCRIPTION         "Write access is not required."

            OBJECT              lecPathSwitchingDelay
            MIN-ACCESS          read-only
            DESCRIPTION         "Write access is not required."

            OBJECT              lecLocalSegmentID
            MIN-ACCESS          read-only
            DESCRIPTION         "Write access is not required."

            OBJECT              lecMulticastSendType
            MIN-ACCESS          read-only
            DESCRIPTION         "Write access is not required."

            OBJECT              lecMulticastSendAvgRate
            MIN-ACCESS          read-only
            DESCRIPTION         "Write access is not required."

            OBJECT              lecMulticastSendPeakRate
            MIN-ACCESS          read-only
            DESCRIPTION         "Write access is not required."

            OBJECT              lecConnectionCompleteTimer
            MIN-ACCESS          read-only
            DESCRIPTION         "Write access is not required."

            OBJECT              lecAtmAddressStatus
            MIN-ACCESS          read-only
            DESCRIPTION         "Write access is not required."

            OBJECT              leArpAtmAddress
            MIN-ACCESS          read-only
            DESCRIPTION         "Write access is not required."

            OBJECT              leArpEntryType
            MIN-ACCESS          read-only
            DESCRIPTION         "Write access is not required."

            OBJECT              leArpRowStatus
            MIN-ACCESS          read-only
            DESCRIPTION         "Write access is not required."

            OBJECT              leRDArpAtmAddress
            MIN-ACCESS          read-only
            DESCRIPTION         "Write access is not required."

            OBJECT              leRDArpEntryType
            MIN-ACCESS          read-only
            DESCRIPTION         "Write access is not required."

            OBJECT              leRDArpRowStatus
            MIN-ACCESS          read-only
            DESCRIPTION         "Write access is not required."

        ::= { leClientMIBCompliances 1 }

        -- Units of Conformance


        leClientConfigGroup    OBJECT-GROUP
                OBJECTS     { lecRowStatus, lecOwner,
                              lecConfigMode,
                              lecConfigLanType,
                              lecConfigMaxDataFrameSize,
                              lecConfigLanName,
                              lecConfigLesAtmAddress,
                              lecControlTimeout,
                              lecMaxUnknownFrameCount,
                              lecMaxUnknownFrameTime,
                              lecVccTimeoutPeriod,
                              lecMaxRetryCount,
                              lecAgingTime,
                              lecForwardDelayTime,
                              lecExpectedArpResponseTime,
                              lecFlushTimeOut,
                              lecPathSwitchingDelay,
                              lecLocalSegmentID,
                              lecMulticastSendType,
                              lecMulticastSendAvgRate,
                              lecMulticastSendPeakRate,
                              lecConnectionCompleteTimer }
                STATUS      current
                DESCRIPTION
                    "A collection of objects used for creating and
                     configuring LAN Emulation Clients."
                ::= { leClientMIBGroups 1 }

        leClientStatusGroup    OBJECT-GROUP
                OBJECTS     { lecIfIndex,
                              lecPrimaryAtmAddress,
                              lecID,
                              lecInterfaceState,
                              lecLastFailureRespCode,
                              lecLastFailureState,
                              lecProtocol, lecVersion,
                              lecTopologyChange,
                              lecConfigServerAtmAddress,
                              lecConfigSource,
                              lecActualLanType,
                              lecActualMaxDataFrameSize,
                              lecActualLanName,
                              lecActualLesAtmAddress,
                              lecProxyClient }
                STATUS      current
                DESCRIPTION
                    "A collection of objects describing the status
                     and operational parameters of the managed LAN
                     Emulation Clients."
                ::= { leClientMIBGroups 2 }

        leClientMappingGroup    OBJECT-GROUP
                OBJECTS     { lecMappingIndex }
                STATUS      current
                DESCRIPTION
                    "A collection of objects which map a LAN Emulation
                     Client's 'ifIndex' to its 'lecIndex'."
                ::= { leClientMIBGroups 3 }

        leClientStatisticsGroup    OBJECT-GROUP
                OBJECTS     { lecArpRequestsOut, lecArpRequestsIn,
                              lecArpRepliesOut , lecArpRepliesIn,
                              lecControlFramesOut,
                              lecControlFramesIn,
                              lecSvcFailures }
                STATUS      current
                DESCRIPTION
                    "A collection of objects which act as an extension
                     to the lecConfigTable.

                     These objects provide statistics on LAN Emulation
                     control traffic and SVC establishment."
                ::= { leClientMIBGroups 4 }

        leClientServerVccGroup    OBJECT-GROUP
                OBJECTS     { lecConfigDirectInterface,
                              lecConfigDirectVpi,
                              lecConfigDirectVci,
                              lecControlDirectInterface,
                              lecControlDirectVpi,
                              lecControlDirectVci,
                              lecControlDistributeInterface,
                              lecControlDistributeVpi,
                              lecControlDistributeVci,
                              lecMulticastSendInterface,
                              lecMulticastSendVpi,
                              lecMulticastSendVci,
                              lecMulticastForwardInterface,
                              lecMulticastForwardVpi,
                              lecMulticastForwardVci }
                STATUS      current
                DESCRIPTION
                    "A collection of objects which act as an extension
                     to the lecConfigTable.

                     These objects identify Configuration Direct,
                     Control, and Multicast VCCs for each client,
                     making it easier to locate their entries in the
                     AToM MIB."
                ::= { leClientMIBGroups 5 }

        leClientAtmAddressesGroup   OBJECT-GROUP
                OBJECTS     { lecAtmAddressStatus }
                STATUS      current
                DESCRIPTION
                    "A collection of objects which describe all of the
                     ATM addresses belonging to each client."
                ::= { leClientMIBGroups 6 }

        leClientMacAddressesGroup   OBJECT-GROUP
                OBJECTS     { lecMacAddressAtmBinding }
                STATUS      current
                DESCRIPTION
                    "A collection of objects which describe all of the
                     MAC addresses registered for each client."
                ::= { leClientMIBGroups 7 }

        leClientRouteDescriptorsGroup    OBJECT-GROUP
                OBJECTS     { lecRouteDescrAtmBinding }
                STATUS      current
                DESCRIPTION
                    "A collection of objects which describe all of the
                     Route Descriptors registered for each client."
                ::= { leClientMIBGroups 8 }

        leClientArpGroup    OBJECT-GROUP
                OBJECTS     { leArpAtmAddress,
                              leArpIsRemoteAddress,
                              leArpEntryType,
                              leArpRowStatus }
                STATUS      current
                DESCRIPTION
                    "A collection of objects which describe the MAC-
                     to-ATM address mappings that this LAN Emulation
                     Client has learned."
                ::= { leClientMIBGroups 9 }

        leClientRDArpGroup    OBJECT-GROUP
                OBJECTS     { leRDArpAtmAddress, leRDArpEntryType,
                              leRDArpRowStatus }
                STATUS      current
                DESCRIPTION
                    "A collection of objects which describe the IEEE
                     802.5 Route Descriptor-to-ATM address mappings
                     that this LAN Emulation Client has learned."
                ::= { leClientMIBGroups 10 }

END
