--
-- RS-XX9-TC-MIB.mi2
-- MIB generated by MG-SOFT Visual MIB Builder 2010 Version 8.0  Build 403
-- Friday, January 22, 2016 at 14:16:48
--

-- *****************************************************************************
-- *****************************************************************************
-- **
-- **  COPYRIGHT      (c) 2011 Rohde & Schwarz GmbH & Co. KG
-- **                          Muehldorfstrasse 15
-- **    R & S                 D-81671 Muenchen
-- **
-- *****************************************************************************
-- **
-- **  MODULE         RS-XX9-TC-MIB
-- **  
-- *****************************************************************************
-- *****************************************************************************

    RS-XX9-TC-MIB DEFINITIONS ::= BEGIN
 
        IMPORTS
            rsXx9MibModule            
                FROM RS-XX9-SMI-MIB            
            Unsigned32, MODULE-IDENTITY            
                FROM SNMPv2-SMI            
            TEXTUAL-CONVENTION            
                FROM SNMPv2-TC;
    
    
        rsXx9TcMibModule MODULE-IDENTITY 
            LAST-UPDATED "201601221400Z"		-- January 22, 2016 at 14:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines textual conventions used in all XX9 MIBs.
                
                The following MIBs are related to this:
                - RS-COMMON-MIB         - mandatory for this MIB.
                - RS-XX9-SMI-MIB        - mandatory for this MIB."
            REVISION "201601221400Z"		-- January 22, 2016 at 14:00 GMT
            DESCRIPTION 
                "add backupTx to Xx9RedundancyMode
                add phu903 to Xx9AmplifierTyoe"
            REVISION "201509240800Z"		-- September 24, 2015 at 08:00 GMT
            DESCRIPTION 
                "add hdRadio to Xx9ModulationMode"
            REVISION "201505211200Z"		-- May 21, 2015 at 12:00 GMT
            DESCRIPTION 
                "add pmu905 to Xx9AmplifierType"
            REVISION "201302151111Z"		-- February 15, 2013 at 11:11 GMT
            DESCRIPTION 
                "modulation modes DAB, DTMB, FM
                amplifier type PHR901"
            REVISION "201205091000Z"		-- May 09, 2012 at 10:00 GMT
            DESCRIPTION 
                "Initial revision"
            REVISION "201108160800Z"		-- August 16, 2011 at 08:00 GMT
            DESCRIPTION 
                "Preliminary version."
            ::= { rsXx9MibModule 1 }

        
    
--
-- Textual conventions
--
    
        EnableOption ::= TEXTUAL-CONVENTION
            STATUS current
            DESCRIPTION 
                "Enabling of a device option."
            SYNTAX INTEGER
                {
                unconfigured(1),
                disabled(2),
                enabled(3)
                }

        IndexAB ::= TEXTUAL-CONVENTION
            STATUS current
            DESCRIPTION 
                "This is used for distinguishing module A (exciterA, outputstageA)
                or B (exciterB, outputstageB) in tables."
            SYNTAX INTEGER
                {
                a(1),
                b(2)
                }

        IndexProgram ::= TEXTUAL-CONVENTION
            STATUS current
            DESCRIPTION 
                "This is used for N+1 systems to indicate a program sent out (logical view).
                ProgramRes(1000) is the reserve program, program1(1) to program8(8) are the main programs.
                In difference to the physical view, programRes(1000) has no special parameters available.
                Furthermore it has no priority."
            SYNTAX INTEGER
                {
                program1(1),
                program2(2),
                program3(3),
                program4(4),
                program5(5),
                program6(6),
                program7(7),
                program8(8),
                programRes(1000)
                }

        IndexTransmitter ::= TEXTUAL-CONVENTION
            STATUS current
            DESCRIPTION 
                "This is used for N+1 systems to indicate a transmitter (physical view).
                TransmitterB(1000) is the reserve transmitter,
                transmitterA1(1) to transmitterA8(8) are the main transmitters.
                In difference to the logical view,
                transmitterB(1000) has special parameters available."
            SYNTAX INTEGER
                {
                transmitterA1(1),
                transmitterA2(2),
                transmitterA3(3),
                transmitterA4(4),
                transmitterA5(5),
                transmitterA6(6),
                transmitterA7(7),
                transmitterA8(8),
                transmitterB(1000)
                }

        NotificationClass ::= TEXTUAL-CONVENTION
            STATUS current
            DESCRIPTION 
                "This is a classification of the highest impact a notification may have
                (the actual impact depends on the notificattion state)
                info(3) - are notifications which only inform about changes, e.g. 'local/remote'
                  or 'reboot of the control unit'. They don't affect the transmission.
                warning(2) - are minor problems which do not influence transmission itself,
                  but may cause a bigger problem when no action is taken, e.g.
                  'RF Loop Program'. Warnings may appear and disappear without the need
                  of acknowledgment.
                fault(1) - have a direct impact on the transmission, e.g.
                  'failure power supply'. Faults never disappear without acknowledgment.
                
                E.g. the commonNtpSync notification from the RS-XX9-COMMON-MIB is classified as warning(2).
                If the state of this notification is fault(3) it is actually a warning,
                otherwise the warning is cancelled."
            SYNTAX INTEGER
                {
                fault(1),
                warning(2),
                info(3)
                }

        NotificationMask ::= TEXTUAL-CONVENTION
            STATUS current
            DESCRIPTION 
                "Enables / Disables a notification.
                enable(1)  --> The notification will be sent in case the NotificationState changes
                disable(2) --> The notification will not be sent."
            SYNTAX INTEGER
                {
                enable(1),
                disable(2)
                }

        NotificationPriority ::= TEXTUAL-CONVENTION
            STATUS current
            DESCRIPTION 
                "The priority of a notification.
                Users can freely set this value in range 0..255."
            SYNTAX Unsigned32 (0..255)

        NotificationState ::= TEXTUAL-CONVENTION
            STATUS current
            DESCRIPTION 
                "The current state of a notification entity:
                off(2)     --> entity is not in service or inactive
                fault(3)   --> entity is faulty
                warning(4) --> entity is in a warning state
                ok(5)      --> entity is on resp. ok"
            SYNTAX INTEGER
                {
                undefined(1),
                off(2),
                fault(3),
                warning(4),
                ok(5)
                }

        SwitchOnOff ::= TEXTUAL-CONVENTION
            STATUS current
            DESCRIPTION 
                "This is for all on/off-switches."
            SYNTAX INTEGER
                {
                on(1),
                off(2)
                }

        Trigger ::= TEXTUAL-CONVENTION
            STATUS current
            DESCRIPTION 
                "Trigger for starting a certain action.
                idle(1)    --> ready, do nothing
                trigger(2) --> do now
                
                A GET will always return idle(1). 
                A SET idle(1) will return NO_ERROR without doing anything."
            SYNTAX INTEGER
                {
                idle(1),
                trigger(2)
                }

        Xx9AmplifierType ::= TEXTUAL-CONVENTION
            STATUS current
            DESCRIPTION 
                "Type of amplifiers for a transmitter."
            SYNTAX INTEGER
                {
                unconfigured(1),
                phu901(2),
                pmu901(3),
                phu902(4),
                phv902(5),
                pmv901(6),
                pmu905(7),
                phu903(8),
                phr901(21)
                }

        Xx9ModulationMode ::= TEXTUAL-CONVENTION
            STATUS current
            DESCRIPTION 
                "Modulation mode."
            SYNTAX INTEGER
                {
                unconfigured(1),
                none(2),
                dvbT2(3),
                dvbT(4),
                isdbT(5),
                atsc(6),
                atv(7),
                dab(8),
                dtmb(9),
                fm(21),
                hdRadioHybrid(22),
                hdRadioFullDigital(23)
                }

        Xx9RedundancyMode ::= TEXTUAL-CONVENTION
            STATUS current
            DESCRIPTION 
                "Redundancy mode of a single transmitter."
            SYNTAX INTEGER
                {
                undefined(1),
                singleDrive(2),
                dualDrive(3),
                backupDrive(4),
                activePa(5),
                backupTx(6)
                }

        Xx9SystemType ::= TEXTUAL-CONVENTION
            STATUS current
            DESCRIPTION 
                "transmitter(2) - single transmitter
                multiTx(3)     - multi Tx system with several transmitters
                nPlus1(4)      - several transmitters in N+1 reserve configuration"
            SYNTAX INTEGER
                {
                unconfigured(1),
                transmitter(2),
                multiTx(3),
                nPlus1(4)
                }

    
--
-- Node definitions
--
    
    
    END

--
-- RS-XX9-TC-MIB.mi2
--
