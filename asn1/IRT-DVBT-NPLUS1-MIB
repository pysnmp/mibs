--
-- IRT-DVBT-NPLUS1-MIB.my
-- MIB generated by MG-SOFT Visual MIB Builder Version 6.0  Build 88
-- Wednesday, May 23, 2007 at 19:04:47
--

	IRT-DVBT-NPLUS1-MIB DEFINITIONS ::= BEGIN
 
		IMPORTS
			objectGroup, eventTimeStamp, eventPriority, eventCounter, mibRelease			
				FROM IRT-COMMONVARBINDS-MIB			
			dvbT, LocalRemote, FaultOK, SelectManualAuto, ReadyNotReady, 
			ExecutedNotExecuted, Input1Input2, SelectOnOff, PresentNotPresent, OkNotOk, 
			WarningOK, MuteOk, SFNMFN			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DateAndTime, DisplayString, TruthValue, TEXTUAL-CONVENTION			
				FROM SNMPv2-TC;
	
	
		-- 1.3.6.1.4.1.19831.1.1.1.5
		dvbnPlus1 MODULE-IDENTITY 
			LAST-UPDATED "200705041400Z"		-- May 04, 2007 at 14:00 GMT
			ORGANIZATION 
				"IRT for WORKING-GROUP-TC-MIB"
			CONTACT-INFO 
				"Contact-info.
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				branch definition
				
				1st level
				
				events                         OBJECT IDENTIFIER ::= { dvbnPlus1 0 }
				dvbnPlus1General               OBJECT IDENTIFIER ::= { dvbnPlus1 1 }
				  dvbnPlus1MainTransmitterTable   is defined below as dvbnPlus1 2
				dvbnPlus1ReserveTransmitter    OBJECT IDENTIFIER ::= { dvbnPlus1 3 }
				  dvbnPlus1TransmitterATable      is defined below as dvbnPlus1 4
				dvbnPlus1TransmitterB          OBJECT IDENTIFIER ::= { dvbnPlus1 5 }
				dvbnPlus1EventEnable           OBJECT IDENTIFIER ::= { dvbnPlus1 6 }
				dvbnPlus1EventPriority         OBJECT IDENTIFIER ::= { dvbnPlus1 7 }
				groups                         OBJECT IDENTIFIER ::= { dvbnPlus1 8 }
				
				
				2nd level
				
				dvbnPlus1EventEnableGeneral                OBJECT IDENTIFIER ::= { dvbnPlus1EventEnable 1 }
				  dvbnPlus1EventEnableMainTransmitterTable    is defined below as dvbnPlus1EventEnable 2
				dvbnPlus1EventEnableReserveTransmitter     OBJECT IDENTIFIER ::= { dvbnPlus1EventEnable 3 }
				  dvbnPlus1EventEnableTransmitterATable       is defined below as dvbnPlus1EventEnable 4 }
				dvbnPlus1EventEnableTransmitterB           OBJECT IDENTIFIER ::= { dvbnPlus1EventEnable 5 }
				
				dvbnPlus1EventPriorityGeneral              OBJECT IDENTIFIER ::= { dvbnPlus1EventPriority 1 }
				  dvbnPlus1EventPriorityMainTransmitterTable  is defined below as dvbnPlus1EventPriority 2
				dvbnPlus1EventPriorityReserveTransmitter   OBJECT IDENTIFIER ::= { dvbnPlus1EventPriority 3 }
				  dvbnPlus1EventPriorityTransmitterATable     is defined below as dvbnPlus1EventPriority 4
				dvbnPlus1EventPriorityTransmitterB         OBJECT IDENTIFIER ::= { dvbnPlus1EventPriority 5 }
				
				end branch"
			REVISION "200705041400Z"		-- May 04, 2007 at 14:00 GMT
			DESCRIPTION 
				"change SFNMode and 
				MODULE-COMPLIANCE
				change numbering: OIDs 
				1.3.6.1.4.1.19831.1.1.1.5.5.x and
				1.3.6.1.4.1.19831.1.1.1.5.6.3.x
				1.3.6.1.4.1.19831.1.1.1.5.6.5.x
				1.3.6.1.4.1.19831.1.1.1.5.7.3.x
				1.3.6.1.4.1.19831.1.1.1.5.7.5.x"
			REVISION "200612211400Z"		-- December 21, 2006 at 14:00 GMT
			DESCRIPTION 
				"TransmitterB corrections
				"
			REVISION "200612201400Z"		-- December 20, 2006 at 14:00 GMT
			DESCRIPTION 
				"Correction"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dvbT 5 }

		
	
--
-- Textual conventions
--
	
		TransmitterBFreeOccupied ::= TEXTUAL-CONVENTION
			STATUS current
			DESCRIPTION 
				"Description. Free/Occupied message for transmitter B
				
				(1) free              
				(2) occupied          "
			SYNTAX INTEGER
				{
				free(1),
				occupied(2)
				}

	
--
-- Node definitions
--
	
-- dvb N+1 Reserve. Events
		-- 1.3.6.1.4.1.19831.1.1.1.5.0
		dvbEventsnPlus1 OBJECT IDENTIFIER ::= { dvbnPlus1 0 }

		
		-- 1.3.6.1.4.1.19831.1.1.1.5.0.1
		dvbnPlus1ResetFaultEvent NOTIFICATION-TYPE
			OBJECTS { sysDescr, sysName, sysLocation, eventTimeStamp, eventPriority, 
				eventCounter, dvbnPlus1ResetFault }
			STATUS obsolete
			DESCRIPTION 
				"Notification is inactive!
				
				Description. dvbnPlus1ResetFault notification"
			::= { dvbEventsnPlus1 1 }

		
		-- 1.3.6.1.4.1.19831.1.1.1.5.0.2
		dvbnPlus1RedundancySwitchOverEvent NOTIFICATION-TYPE
			OBJECTS { sysDescr, sysName, sysLocation, eventTimeStamp, eventPriority, 
				eventCounter, dvbnPlus1RedundancySwitchOver }
			STATUS current
			DESCRIPTION 
				"Description. dvbnPlus1RedundancySwitchOver notification"
			::= { dvbEventsnPlus1 2 }

		
		-- 1.3.6.1.4.1.19831.1.1.1.5.0.3
		dvbnPlus1LocalModeEvent NOTIFICATION-TYPE
			OBJECTS { sysDescr, sysName, sysLocation, eventTimeStamp, eventPriority, 
				eventCounter, dvbnPlus1LocalMode }
			STATUS current
			DESCRIPTION 
				"Description. dvbnPlus1LocalMode notification"
			::= { dvbEventsnPlus1 3 }

		
		-- 1.3.6.1.4.1.19831.1.1.1.5.0.4
		dvbnPlus1ControlUnitFaultEvent NOTIFICATION-TYPE
			OBJECTS { sysDescr, sysName, sysLocation, eventTimeStamp, eventPriority, 
				eventCounter, dvbnPlus1ControlUnitFault }
			STATUS current
			DESCRIPTION 
				"Description. dvbnPlus1ControlUnitFault notification"
			::= { dvbEventsnPlus1 4 }

		
		-- 1.3.6.1.4.1.19831.1.1.1.5.0.5
		dvbnPlus1SwitchOverModeEvent NOTIFICATION-TYPE
			OBJECTS { sysDescr, sysName, sysLocation, eventTimeStamp, eventPriority, 
				eventCounter, dvbnPlus1SwitchOverMode }
			STATUS current
			DESCRIPTION 
				"Description. dvbnPlus1SwitchOverMode notification"
			::= { dvbEventsnPlus1 5 }

		
		-- 1.3.6.1.4.1.19831.1.1.1.5.0.6
		dvbnPlus1SwitchOverReadyEvent NOTIFICATION-TYPE
			OBJECTS { sysDescr, sysName, sysLocation, eventTimeStamp, eventPriority, 
				eventCounter, dvbnPlus1SwitchOverReady }
			STATUS current
			DESCRIPTION 
				"Description. dvbnPlus1SwitchOverReady notification"
			::= { dvbEventsnPlus1 6 }

		
		-- 1.3.6.1.4.1.19831.1.1.1.5.0.7
		dvbnPlus1SwitchOverExecutedEvent NOTIFICATION-TYPE
			OBJECTS { sysDescr, sysName, sysLocation, eventTimeStamp, eventPriority, 
				eventCounter, dvbnPlus1SwitchOverExecuted }
			STATUS current
			DESCRIPTION 
				"Description. dvbnPlus1SwitchOverExecuted notification"
			::= { dvbEventsnPlus1 7 }

		
		-- 1.3.6.1.4.1.19831.1.1.1.5.0.8
		dvbnPlus1SwitchOverFaultEvent NOTIFICATION-TYPE
			OBJECTS { sysDescr, sysName, sysLocation, eventTimeStamp, eventPriority, 
				eventCounter, dvbnPlus1SwitchOverFault }
			STATUS current
			DESCRIPTION 
				"Description. dvbnPlus1SwitchOverFault notification"
			::= { dvbEventsnPlus1 8 }

		
		-- 1.3.6.1.4.1.19831.1.1.1.5.0.9
		dvbnPlus1ChannelSelectionEvent NOTIFICATION-TYPE
			OBJECTS { sysDescr, sysName, sysLocation, eventTimeStamp, eventPriority, 
				eventCounter, dvbnPlus1ChannelSelection }
			STATUS current
			DESCRIPTION 
				"Description. dvbnPlus1ChannelSelection notification"
			::= { dvbEventsnPlus1 9 }

		
		-- 1.3.6.1.4.1.19831.1.1.1.5.0.10
		dvbnPlus1TransmitterBResetEvent NOTIFICATION-TYPE
			OBJECTS { sysDescr, sysName, sysLocation, eventTimeStamp, eventPriority, 
				eventCounter, dvbnPlus1TransmitterBReset }
			STATUS obsolete
			DESCRIPTION 
				"Notification is inactive!
				
				Description. dvbnPlus1TransmitterBReset notification"
			::= { dvbEventsnPlus1 10 }

		
		-- 1.3.6.1.4.1.19831.1.1.1.5.0.11
		dvbnPlus1TransmitterBModeEvent NOTIFICATION-TYPE
			OBJECTS { sysDescr, sysName, sysLocation, eventTimeStamp, eventPriority, 
				eventCounter, dvbnPlus1TransmitterBMode }
			STATUS obsolete
			DESCRIPTION 
				"Notification is inactive!
				
				Description. dvbnPlus1TransmitterBMode notification"
			::= { dvbEventsnPlus1 11 }

		
		-- 1.3.6.1.4.1.19831.1.1.1.5.0.12
		dvbnPlus1MTInputPreselectionEvent NOTIFICATION-TYPE
			OBJECTS { sysDescr, sysName, sysLocation, eventTimeStamp, eventPriority, 
				eventCounter, dvbnPlus1MTInputPreselection, dvbnPlus1EventTransmitterIndex }
			STATUS current
			DESCRIPTION 
				"Description. dvbnPlus1MTInputPreselection notification"
			::= { dvbEventsnPlus1 12 }

		
		-- 1.3.6.1.4.1.19831.1.1.1.5.0.13
		dvbnPlus1MTInputAutomaticEvent NOTIFICATION-TYPE
			OBJECTS { sysDescr, sysName, sysLocation, eventTimeStamp, eventPriority, 
				eventCounter, dvbnPlus1MTInputAutomatic, dvbnPlus1EventTransmitterIndex }
			STATUS current
			DESCRIPTION 
				"Description. dvbnPlus1MTInputAutomatic notification"
			::= { dvbEventsnPlus1 13 }

		
		-- 1.3.6.1.4.1.19831.1.1.1.5.0.14
		dvbnPlus1MTOpModeEvent NOTIFICATION-TYPE
			OBJECTS { sysDescr, sysName, sysLocation, eventTimeStamp, eventPriority, 
				eventCounter, dvbnPlus1MTOpMode, dvbnPlus1EventTransmitterIndex }
			STATUS current
			DESCRIPTION 
				"Description. dvbnPlus1MTOpMode notification"
			::= { dvbEventsnPlus1 14 }

		
		-- 1.3.6.1.4.1.19831.1.1.1.5.0.15
		dvbnPlus1MTRFProgramPresentEvent NOTIFICATION-TYPE
			OBJECTS { sysDescr, sysName, sysLocation, eventTimeStamp, eventPriority, 
				eventCounter, dvbnPlus1MTRFProgramPresent, dvbnPlus1EventTransmitterIndex }
			STATUS current
			DESCRIPTION 
				"Description. dvbnPlus1MTRFProgramPresent notification"
			::= { dvbEventsnPlus1 15 }

		
		-- 1.3.6.1.4.1.19831.1.1.1.5.0.16
		dvbnPlus1RTInputPreselectionEvent NOTIFICATION-TYPE
			OBJECTS { sysDescr, sysName, sysLocation, eventTimeStamp, eventPriority, 
				eventCounter, dvbnPlus1RTInputPreselection }
			STATUS current
			DESCRIPTION 
				"Description. dvbnPlus1RTInputPreselection notification"
			::= { dvbEventsnPlus1 16 }

		
		-- 1.3.6.1.4.1.19831.1.1.1.5.0.17
		dvbnPlus1RTInputAutomaticEvent NOTIFICATION-TYPE
			OBJECTS { sysDescr, sysName, sysLocation, eventTimeStamp, eventPriority, 
				eventCounter, dvbnPlus1RTInputAutomatic }
			STATUS current
			DESCRIPTION 
				"Description. dvbnPlus1RTInputAutomatic notification"
			::= { dvbEventsnPlus1 17 }

		
		-- 1.3.6.1.4.1.19831.1.1.1.5.0.18
		dvbnPlus1RTOpModeEvent NOTIFICATION-TYPE
			OBJECTS { sysDescr, sysName, sysLocation, eventTimeStamp, eventPriority, 
				eventCounter, dvbnPlus1RTOpMode }
			STATUS current
			DESCRIPTION 
				"Description. dvbnPlus1RTOpMode notification"
			::= { dvbEventsnPlus1 18 }

		
		-- 1.3.6.1.4.1.19831.1.1.1.5.0.19
		dvbnPlus1RTRFProgramPresentEvent NOTIFICATION-TYPE
			OBJECTS { sysDescr, sysName, sysLocation, eventTimeStamp, eventPriority, 
				eventCounter, dvbnPlus1RTRFProgramPresent }
			STATUS current
			DESCRIPTION 
				"Description. dvbnPlus1RTRFProgramPresent notification"
			::= { dvbEventsnPlus1 19 }

		
		-- 1.3.6.1.4.1.19831.1.1.1.5.0.20
		dvbnPlus1TARFPresentEvent NOTIFICATION-TYPE
			OBJECTS { sysDescr, sysName, sysLocation, eventTimeStamp, eventPriority, 
				eventCounter, dvbnPlus1TARFPresent, dvbnPlus1EventTransmitterIndex }
			STATUS current
			DESCRIPTION 
				"Description. dvbnPlus1TARFPresent notification"
			::= { dvbEventsnPlus1 20 }

		
		-- 1.3.6.1.4.1.19831.1.1.1.5.0.21
		dvbnPlus1TAInput1OKEvent NOTIFICATION-TYPE
			OBJECTS { sysDescr, sysName, sysLocation, eventTimeStamp, eventPriority, 
				eventCounter, dvbnPlus1TAInput1OK, dvbnPlus1EventTransmitterIndex }
			STATUS current
			DESCRIPTION 
				"Description. dvbnPlus1TAInput1OK notification"
			::= { dvbEventsnPlus1 21 }

		
		-- 1.3.6.1.4.1.19831.1.1.1.5.0.22
		dvbnPlus1TAInput2OKEvent NOTIFICATION-TYPE
			OBJECTS { sysDescr, sysName, sysLocation, eventTimeStamp, eventPriority, 
				eventCounter, dvbnPlus1TAInput2OK, dvbnPlus1EventTransmitterIndex }
			STATUS current
			DESCRIPTION 
				"Description. dvbnPlus1TAInput2OK notification"
			::= { dvbEventsnPlus1 22 }

		
		-- 1.3.6.1.4.1.19831.1.1.1.5.0.23
		dvbnPlus1TALocalModeEvent NOTIFICATION-TYPE
			OBJECTS { sysDescr, sysName, sysLocation, eventTimeStamp, eventPriority, 
				eventCounter, dvbnPlus1TALocalMode, dvbnPlus1EventTransmitterIndex }
			STATUS current
			DESCRIPTION 
				"Description. dvbnPlus1TALocalMode notification"
			::= { dvbEventsnPlus1 23 }

		
		-- 1.3.6.1.4.1.19831.1.1.1.5.0.24
		dvbnPlus1TAInputPreselectionEvent NOTIFICATION-TYPE
			OBJECTS { sysDescr, sysName, sysLocation, eventTimeStamp, eventPriority, 
				eventCounter, dvbnPlus1TAInputPreselection, dvbnPlus1EventTransmitterIndex }
			STATUS current
			DESCRIPTION 
				"Description. dvbnPlus1TAInputPreselection notification"
			::= { dvbEventsnPlus1 24 }

		
		-- 1.3.6.1.4.1.19831.1.1.1.5.0.25
		dvbnPlus1TAInputAutomaticEvent NOTIFICATION-TYPE
			OBJECTS { sysDescr, sysName, sysLocation, eventTimeStamp, eventPriority, 
				eventCounter, dvbnPlus1TAInputAutomatic, dvbnPlus1EventTransmitterIndex }
			STATUS current
			DESCRIPTION 
				"Description. dvbnPlus1TAInputAutomatic notification"
			::= { dvbEventsnPlus1 25 }

		
		-- 1.3.6.1.4.1.19831.1.1.1.5.0.26
		dvbnPlus1TAFaultEvent NOTIFICATION-TYPE
			OBJECTS { sysDescr, sysName, sysLocation, eventTimeStamp, eventPriority, 
				eventCounter, dvbnPlus1TAFault, dvbnPlus1EventTransmitterIndex }
			STATUS current
			DESCRIPTION 
				"Description. dvbnPlus1TAFault notification"
			::= { dvbEventsnPlus1 26 }

		
		-- 1.3.6.1.4.1.19831.1.1.1.5.0.27
		dvbnPlus1TAWarningEvent NOTIFICATION-TYPE
			OBJECTS { sysDescr, sysName, sysLocation, eventTimeStamp, eventPriority, 
				eventCounter, dvbnPlus1TAWarning, dvbnPlus1EventTransmitterIndex }
			STATUS current
			DESCRIPTION 
				"Description. dvbnPlus1TAWarning notification"
			::= { dvbEventsnPlus1 27 }

		
		-- 1.3.6.1.4.1.19831.1.1.1.5.0.28
		dvbnPlus1TAActiveInputEvent NOTIFICATION-TYPE
			OBJECTS { sysDescr, sysName, sysLocation, eventTimeStamp, eventPriority, 
				eventCounter, dvbnPlus1TAActiveInput, dvbnPlus1EventTransmitterIndex }
			STATUS current
			DESCRIPTION 
				"Description. dvbnPlus1TAActiveInput notification"
			::= { dvbEventsnPlus1 28 }

		
		-- 1.3.6.1.4.1.19831.1.1.1.5.0.29
		dvbnPlus1TASFNModeEvent NOTIFICATION-TYPE
			OBJECTS { sysDescr, sysName, sysLocation, eventTimeStamp, eventPriority, 
				eventCounter, dvbnPlus1TASFNMode, dvbnPlus1EventTransmitterIndex }
			STATUS current
			DESCRIPTION 
				"Description. dvbnPlus1TASFNMode notification"
			::= { dvbEventsnPlus1 29 }

		
		-- 1.3.6.1.4.1.19831.1.1.1.5.0.30
		dvbnPlus1TARefFaultEvent NOTIFICATION-TYPE
			OBJECTS { sysDescr, sysName, sysLocation, eventTimeStamp, eventPriority, 
				eventCounter, dvbnPlus1TARefFault, dvbnPlus1EventTransmitterIndex }
			STATUS current
			DESCRIPTION 
				"Description. dvbnPlus1TARefFault notification"
			::= { dvbEventsnPlus1 30 }

		
		-- 1.3.6.1.4.1.19831.1.1.1.5.0.31
		dvbnPlus1TAMuteEvent NOTIFICATION-TYPE
			OBJECTS { sysDescr, sysName, sysLocation, eventTimeStamp, eventPriority, 
				eventCounter, dvbnPlus1TAMute, dvbnPlus1EventTransmitterIndex }
			STATUS current
			DESCRIPTION 
				"Description. dvbnPlus1TAMute notification"
			::= { dvbEventsnPlus1 31 }

		
		-- 1.3.6.1.4.1.19831.1.1.1.5.0.32
		dvbnPlus1TAFaultMIPEvent NOTIFICATION-TYPE
			OBJECTS { sysDescr, sysName, sysLocation, eventTimeStamp, eventPriority, 
				eventCounter, dvbnPlus1TAFaultMIP, dvbnPlus1EventTransmitterIndex }
			STATUS current
			DESCRIPTION 
				"Description. dvbnPlus1TAFaultMIP notification"
			::= { dvbEventsnPlus1 32 }

		
		-- 1.3.6.1.4.1.19831.1.1.1.5.0.33
		dvbnPlus1TAStuffingModeEvent NOTIFICATION-TYPE
			OBJECTS { sysDescr, sysName, sysLocation, eventTimeStamp, eventPriority, 
				eventCounter, dvbnPlus1TAStuffingMode, dvbnPlus1EventTransmitterIndex }
			STATUS current
			DESCRIPTION 
				"Description. dvbnPlus1TAStuffingMode notification"
			::= { dvbEventsnPlus1 33 }

		
		-- 1.3.6.1.4.1.19831.1.1.1.5.0.34
		dvbnPlus1TBRFPresentEvent NOTIFICATION-TYPE
			OBJECTS { sysDescr, sysName, sysLocation, eventTimeStamp, eventPriority, 
				eventCounter, dvbnPlus1TBRFPresent }
			STATUS current
			DESCRIPTION 
				"Description. dvbnPlus1TBRFPresent notification"
			::= { dvbEventsnPlus1 34 }

		
		-- 1.3.6.1.4.1.19831.1.1.1.5.0.35
		dvbnPlus1TBInput1OKEvent NOTIFICATION-TYPE
			OBJECTS { sysDescr, sysName, sysLocation, eventTimeStamp, eventPriority, 
				eventCounter, dvbnPlus1TBInput1OK }
			STATUS current
			DESCRIPTION 
				"Description. dvbnPlus1TBInput1OK notification"
			::= { dvbEventsnPlus1 35 }

		
		-- 1.3.6.1.4.1.19831.1.1.1.5.0.36
		dvbnPlus1TBInput2OKEvent NOTIFICATION-TYPE
			OBJECTS { sysDescr, sysName, sysLocation, eventTimeStamp, eventPriority, 
				eventCounter, dvbnPlus1TBInput2OK }
			STATUS current
			DESCRIPTION 
				"Description. dvbnPlus1TBInput2OK notification"
			::= { dvbEventsnPlus1 36 }

		
		-- 1.3.6.1.4.1.19831.1.1.1.5.0.37
		dvbnPlus1TBLocalModeEvent NOTIFICATION-TYPE
			OBJECTS { sysDescr, sysName, sysLocation, eventTimeStamp, eventPriority, 
				eventCounter, dvbnPlus1TBLocalMode }
			STATUS current
			DESCRIPTION 
				"Description. dvbnPlus1TBLocalMode notification"
			::= { dvbEventsnPlus1 37 }

		
		-- 1.3.6.1.4.1.19831.1.1.1.5.0.38
		dvbnPlus1TBFaultEvent NOTIFICATION-TYPE
			OBJECTS { sysDescr, sysName, sysLocation, eventTimeStamp, eventPriority, 
				eventCounter, dvbnPlus1TBFault }
			STATUS current
			DESCRIPTION 
				"Description. dvbnPlus1TBFault notification"
			::= { dvbEventsnPlus1 38 }

		
		-- 1.3.6.1.4.1.19831.1.1.1.5.0.39
		dvbnPlus1TBWarningEvent NOTIFICATION-TYPE
			OBJECTS { sysDescr, sysName, sysLocation, eventTimeStamp, eventPriority, 
				eventCounter, dvbnPlus1TBWarning }
			STATUS current
			DESCRIPTION 
				"Description. dvbnPlus1TBWarning notification"
			::= { dvbEventsnPlus1 39 }

		
		-- 1.3.6.1.4.1.19831.1.1.1.5.0.40
		dvbnPlus1TBInputPreselectionEvent NOTIFICATION-TYPE
			OBJECTS { sysDescr, sysName, sysLocation, eventTimeStamp, eventPriority, 
				eventCounter, dvbnPlus1TBInputPreselection }
			STATUS current
			DESCRIPTION 
				"Description. dvbnPlus1TBInputPreselection notification"
			::= { dvbEventsnPlus1 40 }

		
		-- 1.3.6.1.4.1.19831.1.1.1.5.0.41
		dvbnPlus1TBInputAutomaticEvent NOTIFICATION-TYPE
			OBJECTS { sysDescr, sysName, sysLocation, eventTimeStamp, eventPriority, 
				eventCounter, dvbnPlus1TBInputAutomatic }
			STATUS current
			DESCRIPTION 
				"Description. dvbnPlus1TBInputAutomatic notification"
			::= { dvbEventsnPlus1 41 }

		
		-- 1.3.6.1.4.1.19831.1.1.1.5.0.42
		dvbnPlus1TBActiveInputEvent NOTIFICATION-TYPE
			OBJECTS { sysDescr, sysName, sysLocation, eventTimeStamp, eventPriority, 
				eventCounter, dvbnPlus1TBActiveInput }
			STATUS current
			DESCRIPTION 
				"Description. dvbnPlus1TBActiveInput notification"
			::= { dvbEventsnPlus1 42 }

		
		-- 1.3.6.1.4.1.19831.1.1.1.5.0.43
		dvbnPlus1TBSFNModeEvent NOTIFICATION-TYPE
			OBJECTS { sysDescr, sysName, sysLocation, eventTimeStamp, eventPriority, 
				eventCounter, dvbnPlus1TBSFNMode }
			STATUS current
			DESCRIPTION 
				"Description. dvbnPlus1TBSFNMode notification"
			::= { dvbEventsnPlus1 43 }

		
		-- 1.3.6.1.4.1.19831.1.1.1.5.0.44
		dvbnPlus1TBRefFaultEvent NOTIFICATION-TYPE
			OBJECTS { sysDescr, sysName, sysLocation, eventTimeStamp, eventPriority, 
				eventCounter, dvbnPlus1TBRefFault }
			STATUS current
			DESCRIPTION 
				"Description. dvbnPlus1TBRefFault notification"
			::= { dvbEventsnPlus1 44 }

		
		-- 1.3.6.1.4.1.19831.1.1.1.5.0.45
		dvbnPlus1TBMuteEvent NOTIFICATION-TYPE
			OBJECTS { sysDescr, sysName, sysLocation, eventTimeStamp, eventPriority, 
				eventCounter, dvbnPlus1TBMute }
			STATUS current
			DESCRIPTION 
				"Description. dvbnPlus1TBMute notification"
			::= { dvbEventsnPlus1 45 }

		
		-- 1.3.6.1.4.1.19831.1.1.1.5.0.46
		dvbnPlus1TBFaultMIPEvent NOTIFICATION-TYPE
			OBJECTS { sysDescr, sysName, sysLocation, eventTimeStamp, eventPriority, 
				eventCounter, dvbnPlus1TBFaultMIP }
			STATUS current
			DESCRIPTION 
				"Description. dvbnPlus1TBFaultMIP notification"
			::= { dvbEventsnPlus1 46 }

		
		-- 1.3.6.1.4.1.19831.1.1.1.5.0.47
		dvbnPlus1TBStuffingModeEvent NOTIFICATION-TYPE
			OBJECTS { sysDescr, sysName, sysLocation, eventTimeStamp, eventPriority, 
				eventCounter, dvbnPlus1TBStuffingMode }
			STATUS current
			DESCRIPTION 
				"Description. dvbnPlus1TBStuffingMode notification"
			::= { dvbEventsnPlus1 47 }

		
-- dvb N+1 Resreve. General
		-- 1.3.6.1.4.1.19831.1.1.1.5.1
		dvbnPlus1General OBJECT IDENTIFIER ::= { dvbnPlus1 1 }

		
		-- 1.3.6.1.4.1.19831.1.1.1.5.1.1
		dvbnPlus1ResetFault OBJECT-TYPE
			SYNTAX Unsigned32
			MAX-ACCESS read-write
			STATUS obsolete
			DESCRIPTION
				"Description. Massage is inactive!
				
				trigger for reset the sum fault
				
				<1>
				
				(1) reset sum fault"
			::= { dvbnPlus1General 1 }

		
		-- 1.3.6.1.4.1.19831.1.1.1.5.1.2
		dvbnPlus1RedundancySwitchOver OBJECT-TYPE
			SYNTAX INTEGER (-1..6)
			MAX-ACCESS read-write
			STATUS current
			DESCRIPTION
				"N+1 reserve. Redundancy reserve switch over for transmitters B,A1,A2...An
				
				<-1,0,1,2,3,4,...,n>
				
				(-1) reserve transmitter B
				(0)  undefined
				(1)  transmitter 1
				(2)  transmitter 2
				(3)  transmitter 3
				(4)  transmitter 4
				.................
				(n) transmitter n
				"
			::= { dvbnPlus1General 2 }

		
		-- 1.3.6.1.4.1.19831.1.1.1.5.1.3
		dvbnPlus1LocalMode OBJECT-TYPE
			SYNTAX LocalRemote
			MAX-ACCESS read-only
			STATUS current
			DESCRIPTION
				"N+1 reserve. Local mode
				
				(0) undefined
				(1) local
				(2) remote
				"
			::= { dvbnPlus1General 3 }

		
		-- 1.3.6.1.4.1.19831.1.1.1.5.1.4
		dvbnPlus1ControlUnitFault OBJECT-TYPE
			SYNTAX FaultOK
			MAX-ACCESS read-only
			STATUS current
			DESCRIPTION
				"N+1 reserve. State of the control unit
				
				(0) undefined
				(1) fault
				(2) ok"
			::= { dvbnPlus1General 4 }

		
		-- 1.3.6.1.4.1.19831.1.1.1.5.1.5
		dvbnPlus1SwitchOverMode OBJECT-TYPE
			SYNTAX SelectManualAuto
			MAX-ACCESS read-write
			STATUS current
			DESCRIPTION
				"N+1 reserve. Switch over mode: manual or automatic
				
				(0) undefined
				(1) manual 
				(2) automatic"
			::= { dvbnPlus1General 5 }

		
		-- 1.3.6.1.4.1.19831.1.1.1.5.1.6
		dvbnPlus1SwitchOverReady OBJECT-TYPE
			SYNTAX ReadyNotReady
			MAX-ACCESS read-only
			STATUS current
			DESCRIPTION
				"State of the N+1 reserve  switch over unit
				
				(0) undefined
				(1) ready
				(2) not ready"
			::= { dvbnPlus1General 6 }

		
		-- 1.3.6.1.4.1.19831.1.1.1.5.1.7
		dvbnPlus1SwitchOverExecuted OBJECT-TYPE
			SYNTAX ExecutedNotExecuted
			MAX-ACCESS read-only
			STATUS current
			DESCRIPTION
				"N+1 reserve. Shows if the reserve switsch over uinit it has executed
				
				(0) undefined
				(1) executed
				(2) not executed"
			::= { dvbnPlus1General 7 }

		
		-- 1.3.6.1.4.1.19831.1.1.1.5.1.8
		dvbnPlus1SwitchOverFault OBJECT-TYPE
			SYNTAX FaultOK
			MAX-ACCESS read-only
			STATUS current
			DESCRIPTION
				"N+1 reserve. Fault state of the switch over unit
				
				(0) undefined
				(1) faulty
				(2) ok"
			::= { dvbnPlus1General 8 }

		
		-- 1.3.6.1.4.1.19831.1.1.1.5.1.9
		dvbnPlus1ChannelSelection OBJECT-TYPE
			SYNTAX Unsigned32
			MAX-ACCESS read-write
			STATUS current
			DESCRIPTION
				"N+1 reserve. Chanel selection 1...n of reserve transmitter
				
				<0,1,2,...,n>
				
				(0) undefined
				(1) chanel 1
				(2) chanel 2
				...
				(n) chanel n
				
				"
			::= { dvbnPlus1General 9 }

		
		-- 1.3.6.1.4.1.19831.1.1.1.5.1.10
		dvbnPlus1TransmitterBReset OBJECT-TYPE
			SYNTAX Unsigned32
			MAX-ACCESS read-write
			STATUS obsolete
			DESCRIPTION
				"Message is inactive!
				
				
				N+1 Reserve. Transmitter B reset: trigger for reset 
				
				<1>
				
				(1) reset fault
				"
			::= { dvbnPlus1General 10 }

		
		-- 1.3.6.1.4.1.19831.1.1.1.5.1.11
		dvbnPlus1TransmitterBMode OBJECT-TYPE
			SYNTAX TransmitterBFreeOccupied
			MAX-ACCESS read-only
			STATUS obsolete
			DESCRIPTION
				"Message is inactive!
				
				N+1 reserve. Transmitter B redundancy state
				
				(1) free
				(2) occupied
				"
			::= { dvbnPlus1General 11 }

		
		-- 1.3.6.1.4.1.19831.1.1.1.5.1.12
		dvbnPlus1EventTransmitterIndex OBJECT-TYPE
			SYNTAX Unsigned32 (1..255)
			MAX-ACCESS read-only
			STATUS current
			DESCRIPTION
				"N+1 reserve. Event index to be transmitted along which each trap from MaintransmitterTable or TransmitterATable"
			::= { dvbnPlus1General 12 }

		
-- dvb N+1 reserve. Main transmitter table
		-- 1.3.6.1.4.1.19831.1.1.1.5.2
		dvbnPlus1MainTransmitterTable OBJECT-TYPE
			SYNTAX SEQUENCE OF DvbnPlus1MainTransmitterEntry
			MAX-ACCESS not-accessible
			STATUS current
			DESCRIPTION
				"Table of logical transmitters carrying programs
				"
			::= { dvbnPlus1 2 }

		
-- dvb N+1 reserve: One logical transmitter, numbered from 1 to n
		-- 1.3.6.1.4.1.19831.1.1.1.5.2.1
		dvbnPlus1MainTransmitterEntry OBJECT-TYPE
			SYNTAX DvbnPlus1MainTransmitterEntry
			MAX-ACCESS not-accessible
			STATUS current
			DESCRIPTION
				"One logical transmitter, numbered from 1 to n"
			INDEX { dvbnPlus1MTIndex }
			::= { dvbnPlus1MainTransmitterTable 1 }

		
		DvbnPlus1MainTransmitterEntry ::=
			SEQUENCE { 
				dvbnPlus1MTIndex
					Unsigned32,
				dvbnPlus1MTInputPreselection
					Input1Input2,
				dvbnPlus1MTInputAutomatic
					SelectOnOff,
				dvbnPlus1MTOpMode
					SelectOnOff,
				dvbnPlus1MTRFProgramPresent
					PresentNotPresent
			 }

		-- 1.3.6.1.4.1.19831.1.1.1.5.2.1.1
		dvbnPlus1MTIndex OBJECT-TYPE
			SYNTAX Unsigned32 (1..255)
			MAX-ACCESS read-only
			STATUS current
			DESCRIPTION
				"N+1 Reserve. Main transmitter index
				
				<1,2,3,4,5,6>
				
				(1) transmitter 1
				(2) transmitter 2
				(3) transmitter 3
				(4) transmitter 4
				(5) transmitter 5
				(6) transmitter 6
				"
			::= { dvbnPlus1MainTransmitterEntry 1 }

		
		-- 1.3.6.1.4.1.19831.1.1.1.5.2.1.2
		dvbnPlus1MTInputPreselection OBJECT-TYPE
			SYNTAX Input1Input2
			MAX-ACCESS read-write
			STATUS current
			DESCRIPTION
				"Important! This message (logical view) is redundant with analogue massage 
				dvbnPlus1TAInputPreselection OID: 1.3.6.1.4.1.19831.1.1.1.5.4.1.6
				below the node dvbnPlus1TransmitterATable. 
				In the operation system mandatory there must be used only one of these views:
				
				 logical
				or
				 physical
				
				N+1 Reserve.Main transmitter preselection  input 
				
				(0) undefined
				(1) Input 1
				(2) Input 2"
			::= { dvbnPlus1MainTransmitterEntry 2 }

		
		-- 1.3.6.1.4.1.19831.1.1.1.5.2.1.3
		dvbnPlus1MTInputAutomatic OBJECT-TYPE
			SYNTAX SelectOnOff
			MAX-ACCESS read-write
			STATUS current
			DESCRIPTION
				"Important! This message (logical view) is redundant with analogue massage 
				dvbnPlus1TAInputAutomatic OID: 1.3.6.1.4.1.19831.1.1.1.5.4.1.7
				below the node dvbnPlus1TransmitterATable. 
				In the operation system mandatory there must be used only one of these views:
				
				 logical
				or
				 physical
				
				N+1 Reserve. Main transmitter reserve input
				
				(0) undefined
				(1) ON 
				(2) OFF "
			::= { dvbnPlus1MainTransmitterEntry 3 }

		
		-- 1.3.6.1.4.1.19831.1.1.1.5.2.1.4
		dvbnPlus1MTOpMode OBJECT-TYPE
			SYNTAX SelectOnOff
			MAX-ACCESS read-write
			STATUS current
			DESCRIPTION
				"N+1 Reserve. General transmitter control 
				
				(0) undefined
				(1) ON
				(2) OFF"
			::= { dvbnPlus1MainTransmitterEntry 4 }

		
		-- 1.3.6.1.4.1.19831.1.1.1.5.2.1.5
		dvbnPlus1MTRFProgramPresent OBJECT-TYPE
			SYNTAX PresentNotPresent
			MAX-ACCESS read-only
			STATUS current
			DESCRIPTION
				"N+1 reserve. Describes if the output power of the   main transmitter is present
				
				(0) undefined
				(1) present
				(2) not present
				"
			::= { dvbnPlus1MainTransmitterEntry 5 }

		
-- dvb N+1 reserve. Reserve Transmitter
		-- 1.3.6.1.4.1.19831.1.1.1.5.3
		dvbnPlus1ReserveTransmitter OBJECT IDENTIFIER ::= { dvbnPlus1 3 }

		
		-- 1.3.6.1.4.1.19831.1.1.1.5.3.2
		dvbnPlus1RTInputPreselection OBJECT-TYPE
			SYNTAX Input1Input2
			MAX-ACCESS read-write
			STATUS current
			DESCRIPTION
				"Important! This message (logical view) is redundant with analogue massage 
				dvbnPlus1TBInputPreselection OID: 1.3.6.1.4.1.19831.1.1.1.5.5.5
				below the node dvbnPlus1Transmitter B. 
				In the operation system mandatory there must be used only one of these views:
				
				 logical
				or
				 physical
				
				N+1 reserve. Preselection input reserve transmitter  
				
				(0) undefined
				(1) Input 1
				(2) Input 2"
			::= { dvbnPlus1ReserveTransmitter 2 }

		
		-- 1.3.6.1.4.1.19831.1.1.1.5.3.3
		dvbnPlus1RTInputAutomatic OBJECT-TYPE
			SYNTAX SelectOnOff
			MAX-ACCESS read-write
			STATUS current
			DESCRIPTION
				"Important! This message (logical view) is redundant with analogue massage 
				dvbnPlus1TBInputAutomatic OID: 1.3.6.1.4.1.19831.1.1.1.5.5.6
				below the node dvbnPlus1TransmitterB. 
				In the operation system mandatory there must be used only one of these views:
				
				 logical
				or
				 physical
				
				
				
				N+1 reserve. Reserve transmitter control 
				
				(0) undefined
				(1) ON 
				(2) OFF "
			::= { dvbnPlus1ReserveTransmitter 3 }

		
		-- 1.3.6.1.4.1.19831.1.1.1.5.3.4
		dvbnPlus1RTOpMode OBJECT-TYPE
			SYNTAX SelectOnOff
			MAX-ACCESS read-write
			STATUS current
			DESCRIPTION
				"N+1 reserve. reserve transmitter control
				
				(0) undefined
				(1) ON
				(2) OFF"
			::= { dvbnPlus1ReserveTransmitter 4 }

		
		-- 1.3.6.1.4.1.19831.1.1.1.5.3.5
		dvbnPlus1RTRFProgramPresent OBJECT-TYPE
			SYNTAX PresentNotPresent
			MAX-ACCESS read-only
			STATUS current
			DESCRIPTION
				"N+1 reserve. Describes if the output power of the   reserve transmitter is present
				
				(0) undefined
				(1) present
				(2) not present"
			::= { dvbnPlus1ReserveTransmitter 5 }

		
-- dvb n+1 reserve. Transmitter A table
		-- 1.3.6.1.4.1.19831.1.1.1.5.4
		dvbnPlus1TransmitterATable OBJECT-TYPE
			SYNTAX SEQUENCE OF DvbnPlus1TransmitterAEntry
			MAX-ACCESS not-accessible
			STATUS current
			DESCRIPTION
				"Table of physical transmitters ment to be on air in normal operation"
			::= { dvbnPlus1 4 }

		
-- dvb n+1 reserve: transmitter A entry - rows
		-- 1.3.6.1.4.1.19831.1.1.1.5.4.1
		dvbnPlus1TransmitterAEntry OBJECT-TYPE
			SYNTAX DvbnPlus1TransmitterAEntry
			MAX-ACCESS not-accessible
			STATUS current
			DESCRIPTION
				"N+1 reserve. One physical transmitter, numbered from A1 to An"
			INDEX { dvbnPlus1TAIndex }
			::= { dvbnPlus1TransmitterATable 1 }

		
		DvbnPlus1TransmitterAEntry ::=
			SEQUENCE { 
				dvbnPlus1TAIndex
					Unsigned32,
				dvbnPlus1TARFPresent
					PresentNotPresent,
				dvbnPlus1TAInput1OK
					OkNotOk,
				dvbnPlus1TAInput2OK
					OkNotOk,
				dvbnPlus1TALocalMode
					LocalRemote,
				dvbnPlus1TAInputPreselection
					Input1Input2,
				dvbnPlus1TAInputAutomatic
					SelectManualAuto,
				dvbnPlus1TAFault
					FaultOK,
				dvbnPlus1TAWarning
					WarningOK,
				dvbnPlus1TAActiveInput
					INTEGER,
				dvbnPlus1TASFNMode
					SFNMFN,
				dvbnPlus1TARefFault
					FaultOK,
				dvbnPlus1TAMute
					MuteOk,
				dvbnPlus1TAFaultMIP
					FaultOK,
				dvbnPlus1TAStuffingMode
					SelectOnOff
			 }

		-- 1.3.6.1.4.1.19831.1.1.1.5.4.1.1
		dvbnPlus1TAIndex OBJECT-TYPE
			SYNTAX Unsigned32 (1..255)
			MAX-ACCESS read-only
			STATUS current
			DESCRIPTION
				"N+1 reserve. Index of the  transmitters A1,A2...An
				
				"
			::= { dvbnPlus1TransmitterAEntry 1 }

		
		-- 1.3.6.1.4.1.19831.1.1.1.5.4.1.2
		dvbnPlus1TARFPresent OBJECT-TYPE
			SYNTAX PresentNotPresent
			MAX-ACCESS read-only
			STATUS current
			DESCRIPTION
				"N+1 reserve. Describes if the output power of the  transmitter A is present
				
				(0) undefined
				(1) present
				(2) not present"
			::= { dvbnPlus1TransmitterAEntry 2 }

		
		-- 1.3.6.1.4.1.19831.1.1.1.5.4.1.3
		dvbnPlus1TAInput1OK OBJECT-TYPE
			SYNTAX OkNotOk
			MAX-ACCESS read-only
			STATUS current
			DESCRIPTION
				"N+1 reserve. Describes if the input signal at the input 1 of  transmitter A is ok
				
				(0) undefined
				(1) signal ok
				(2) signal is not ok"
			::= { dvbnPlus1TransmitterAEntry 3 }

		
		-- 1.3.6.1.4.1.19831.1.1.1.5.4.1.4
		dvbnPlus1TAInput2OK OBJECT-TYPE
			SYNTAX OkNotOk
			MAX-ACCESS read-only
			STATUS current
			DESCRIPTION
				"N+1 reserve. Describes if the input signal at the input 2 of  transmitter A is ok
				
				(0) undefined
				(1) signal ok
				(2) signal is not ok"
			::= { dvbnPlus1TransmitterAEntry 4 }

		
		-- 1.3.6.1.4.1.19831.1.1.1.5.4.1.5
		dvbnPlus1TALocalMode OBJECT-TYPE
			SYNTAX LocalRemote
			MAX-ACCESS read-only
			STATUS current
			DESCRIPTION
				"N+1 reserve. Local mode of the  transmitter A
				
				(0) undefined
				(1) local
				(2) remote
				"
			::= { dvbnPlus1TransmitterAEntry 5 }

		
		-- 1.3.6.1.4.1.19831.1.1.1.5.4.1.6
		dvbnPlus1TAInputPreselection OBJECT-TYPE
			SYNTAX Input1Input2
			MAX-ACCESS read-write
			STATUS current
			DESCRIPTION
				"
				Important! This message (logical view) is redundant with analogue massage 
				dvbnPlus1MTInputPreselection OID: 1.3.6.1.4.1.19831.1.1.1.5.2.1.2
				below the node dvbnPlus1MainTransmitterTable. 
				In the operation system mandatory there must be used only one of these views:
				
				 logical
				or
				 physical
				
				N+1 reserve. Preselection input of transmitter A
				
				(0) undefined
				(1) Input 1
				(2) Input 2"
			::= { dvbnPlus1TransmitterAEntry 6 }

		
		-- 1.3.6.1.4.1.19831.1.1.1.5.4.1.7
		dvbnPlus1TAInputAutomatic OBJECT-TYPE
			SYNTAX SelectManualAuto
			MAX-ACCESS read-write
			STATUS current
			DESCRIPTION
				"Important! This message (logical view) is redundant with analogue massage 
				dvbnPlus1MTInputAutomatic OID: 1.3.6.1.4.1.19831.1.1.1.5.2.1.3
				below the node dvbnPlus1MainTransmitterTable. 
				In the operation system mandatory there must be used only one of these views:
				
				 logical
				or
				 physical
				
				N+1 reserve. Input selection mode of the transmitter A:  manual or automatic
				
				(0) undefined
				(1) manual 
				(2) automatic"
			::= { dvbnPlus1TransmitterAEntry 7 }

		
		-- 1.3.6.1.4.1.19831.1.1.1.5.4.1.8
		dvbnPlus1TAFault OBJECT-TYPE
			SYNTAX FaultOK
			MAX-ACCESS read-only
			STATUS current
			DESCRIPTION
				"N+1 reserve. Fault state of the transmitter A
				
				(0) undefined
				(1) fault
				(2) ok"
			::= { dvbnPlus1TransmitterAEntry 8 }

		
		-- 1.3.6.1.4.1.19831.1.1.1.5.4.1.9
		dvbnPlus1TAWarning OBJECT-TYPE
			SYNTAX WarningOK
			MAX-ACCESS read-only
			STATUS current
			DESCRIPTION
				"N+1 reserve. Warning state of transmiter A
				
				(0) undefined
				(1) warning
				(2) ok"
			::= { dvbnPlus1TransmitterAEntry 9 }

		
		-- 1.3.6.1.4.1.19831.1.1.1.5.4.1.10
		dvbnPlus1TAActiveInput OBJECT-TYPE
			SYNTAX INTEGER
				{
				undefined(0),
				input1(1),
				input2(2),
				seamless(3),
				hmHierarchicalModulation(4)
				}
			MAX-ACCESS read-only
			STATUS current
			DESCRIPTION
				"N+1 reserve. Active input of the transmitter A  
				
				"
			::= { dvbnPlus1TransmitterAEntry 10 }

		
		-- 1.3.6.1.4.1.19831.1.1.1.5.4.1.11
		dvbnPlus1TASFNMode OBJECT-TYPE
			SYNTAX SFNMFN
			MAX-ACCESS read-only
			STATUS current
			DESCRIPTION
				"N+1 reserve. SFN mode of transmitter A
				
				(0) undefined
				(1) SFN
				(2) MFN
				"
			::= { dvbnPlus1TransmitterAEntry 11 }

		
		-- 1.3.6.1.4.1.19831.1.1.1.5.4.1.12
		dvbnPlus1TARefFault OBJECT-TYPE
			SYNTAX FaultOK
			MAX-ACCESS read-only
			STATUS current
			DESCRIPTION
				"N+1 reserve. FAult state of the GPS input or reference frequency of transmitter A
				
				(0) undefined
				(1) fault
				(2) ok"
			::= { dvbnPlus1TransmitterAEntry 12 }

		
		-- 1.3.6.1.4.1.19831.1.1.1.5.4.1.13
		dvbnPlus1TAMute OBJECT-TYPE
			SYNTAX MuteOk
			MAX-ACCESS read-only
			STATUS current
			DESCRIPTION
				"N+1 reserve. Mute state of transmitter A
				
				(0) undefined
				(1) mute
				(2) ok"
			::= { dvbnPlus1TransmitterAEntry 13 }

		
		-- 1.3.6.1.4.1.19831.1.1.1.5.4.1.14
		dvbnPlus1TAFaultMIP OBJECT-TYPE
			SYNTAX FaultOK
			MAX-ACCESS read-only
			STATUS current
			DESCRIPTION
				"N+1 reserve. MIP fault state of transmitter A
				
				(0) undefined
				(1) fault
				(2) ok"
			::= { dvbnPlus1TransmitterAEntry 14 }

		
		-- 1.3.6.1.4.1.19831.1.1.1.5.4.1.15
		dvbnPlus1TAStuffingMode OBJECT-TYPE
			SYNTAX SelectOnOff
			MAX-ACCESS read-only
			STATUS current
			DESCRIPTION
				"N+1 reserve. Stuffing state of transmitter A
				
				(0) undefined
				(1) ON 
				(2) OFF "
			::= { dvbnPlus1TransmitterAEntry 15 }

		
-- dvb N+1. Transmitter B
		-- 1.3.6.1.4.1.19831.1.1.1.5.5
		dvbnPlus1TransmitterB OBJECT IDENTIFIER ::= { dvbnPlus1 5 }

		
		-- 1.3.6.1.4.1.19831.1.1.1.5.5.2
		dvbnPlus1TBRFPresent OBJECT-TYPE
			SYNTAX PresentNotPresent
			MAX-ACCESS read-only
			STATUS current
			DESCRIPTION
				"n+1 reserve:  Describes if the output power of the  transmitter B is present
				
				(0) undefined
				(1) present
				(2) not present"
			::= { dvbnPlus1TransmitterB 2 }

		
		-- 1.3.6.1.4.1.19831.1.1.1.5.5.3
		dvbnPlus1TBInput1OK OBJECT-TYPE
			SYNTAX OkNotOk
			MAX-ACCESS read-only
			STATUS current
			DESCRIPTION
				"N+1 reserve. Describes if the input signal at the input 1 of reserve is ok
				
				(0) undefined
				(1) signal ok
				(2) signal not ok "
			::= { dvbnPlus1TransmitterB 3 }

		
		-- 1.3.6.1.4.1.19831.1.1.1.5.5.4
		dvbnPlus1TBInput2OK OBJECT-TYPE
			SYNTAX OkNotOk
			MAX-ACCESS read-only
			STATUS current
			DESCRIPTION
				"N+1 reserve. Describes if the input signal at the input 2 of reserve is ok
				
				(0) undefined
				(1) signal ok
				(2) signal not ok "
			::= { dvbnPlus1TransmitterB 4 }

		
		-- 1.3.6.1.4.1.19831.1.1.1.5.5.5
		dvbnPlus1TBLocalMode OBJECT-TYPE
			SYNTAX LocalRemote
			MAX-ACCESS read-only
			STATUS current
			DESCRIPTION
				"N+1 reserve. Reserve local mode: Describes the output Power of the  transmitter B
				
				(0) undefined
				(1) local
				(2) remote
				"
			::= { dvbnPlus1TransmitterB 5 }

		
		-- 1.3.6.1.4.1.19831.1.1.1.5.5.6
		dvbnPlus1TBInputPreselection OBJECT-TYPE
			SYNTAX Input1Input2
			MAX-ACCESS read-write
			STATUS current
			DESCRIPTION
				"Important! This message (logical view) is redundant with analogue massage 
				dvbnPlus1RTInputPreselectionReserve OID: 1.3.6.1.4.1.19831.1.1.1.5.3.1
				below the node dvbnPlus1ReserveTransmitter. 
				In the operation system mandatory there must be used only one of these views:
				
				 logical
				or
				 physical
				
				N+1 reserve. Preselection input reserve transmitter  
				
				(0) undefined
				(1) Input 1
				(2) Input 2
				
				
				"
			::= { dvbnPlus1TransmitterB 6 }

		
		-- 1.3.6.1.4.1.19831.1.1.1.5.5.7
		dvbnPlus1TBInputAutomatic OBJECT-TYPE
			SYNTAX SelectManualAuto
			MAX-ACCESS read-write
			STATUS current
			DESCRIPTION
				"Important! This message (logical view) is redundant with analogue massage 
				dvbnPlus1RTInputAutomaticReserve OID: 1.3.6.1.4.1.19831.1.1.1.5.3.2
				below the node dvbnPlus1TransmitterB. 
				In the operation system mandatory there must be used only one of these views:
				
				 logical
				or
				 physical
				
				
				N+1 reserve. Reserve input selection mode: manual or automatic
				
				(0) undefined
				(1) manual 
				(2) automatic"
			::= { dvbnPlus1TransmitterB 7 }

		
		-- 1.3.6.1.4.1.19831.1.1.1.5.5.8
		dvbnPlus1TBFault OBJECT-TYPE
			SYNTAX FaultOK
			MAX-ACCESS read-only
			STATUS current
			DESCRIPTION
				"N+1 reserve. Fault state of reserve 
				
				(0) undefined
				(1) fault
				(2) ok"
			::= { dvbnPlus1TransmitterB 8 }

		
		-- 1.3.6.1.4.1.19831.1.1.1.5.5.9
		dvbnPlus1TBWarning OBJECT-TYPE
			SYNTAX WarningOK
			MAX-ACCESS read-only
			STATUS current
			DESCRIPTION
				"n+1 reserve. Warning state of reserve
				
				(0) undefined
				(1) warning
				(2) ok"
			::= { dvbnPlus1TransmitterB 9 }

		
		-- 1.3.6.1.4.1.19831.1.1.1.5.5.10
		dvbnPlus1TBActiveInput OBJECT-TYPE
			SYNTAX INTEGER
				{
				undefined(0),
				input1(1),
				input2(2),
				seamless(3),
				hmHierarchicalModulation(4)
				}
			MAX-ACCESS read-only
			STATUS current
			DESCRIPTION
				"N+1 reserve. Active input of the reserve
				
				
				"
			::= { dvbnPlus1TransmitterB 10 }

		
		-- 1.3.6.1.4.1.19831.1.1.1.5.5.11
		dvbnPlus1TBSFNMode OBJECT-TYPE
			SYNTAX SFNMFN
			MAX-ACCESS read-only
			STATUS current
			DESCRIPTION
				"N+1 reserve. SFN mode of reserve
				
				(0) undefined
				(1) SFN
				(2) MFN
				
				
				
				
				"
			::= { dvbnPlus1TransmitterB 11 }

		
		-- 1.3.6.1.4.1.19831.1.1.1.5.5.12
		dvbnPlus1TBRefFault OBJECT-TYPE
			SYNTAX FaultOK
			MAX-ACCESS read-only
			STATUS current
			DESCRIPTION
				"N+1 reserve. Fault state of the GPS input or the reference frequency of reserve transmitter
				
				(0) undefined
				(1) fault
				(2) ok"
			::= { dvbnPlus1TransmitterB 12 }

		
		-- 1.3.6.1.4.1.19831.1.1.1.5.5.13
		dvbnPlus1TBMute OBJECT-TYPE
			SYNTAX MuteOk
			MAX-ACCESS read-only
			STATUS current
			DESCRIPTION
				"N+1 reserve. Mute state of reserve
				
				(0) undefined
				(1) mute
				(2) ok"
			::= { dvbnPlus1TransmitterB 13 }

		
		-- 1.3.6.1.4.1.19831.1.1.1.5.5.14
		dvbnPlus1TBFaultMIP OBJECT-TYPE
			SYNTAX FaultOK
			MAX-ACCESS read-only
			STATUS current
			DESCRIPTION
				"N+1 reserve. MIP fault state of reserve
				
				(0) undefined
				(1) fault
				(2) ok"
			::= { dvbnPlus1TransmitterB 14 }

		
		-- 1.3.6.1.4.1.19831.1.1.1.5.5.15
		dvbnPlus1TBStuffingMode OBJECT-TYPE
			SYNTAX SelectOnOff
			MAX-ACCESS read-only
			STATUS current
			DESCRIPTION
				"N+1 reserve. Stuffing state of reserve
				
				(0) undefined
				(1) ON 
				(2) OFF"
			::= { dvbnPlus1TransmitterB 15 }

		
-- dvb N+1 reserve. Switch for event 
		-- 1.3.6.1.4.1.19831.1.1.1.5.6
		dvbnPlus1EventEnable OBJECT IDENTIFIER ::= { dvbnPlus1 6 }

		
-- dvb N+1 reserve. general:  events 
		-- 1.3.6.1.4.1.19831.1.1.1.5.6.1
		dvbnPlus1EventEnableGeneral OBJECT IDENTIFIER ::= { dvbnPlus1EventEnable 1 }

		
		-- 1.3.6.1.4.1.19831.1.1.1.5.6.1.1
		dvbnPlus1ResetFaultEnable OBJECT-TYPE
			SYNTAX TruthValue
			MAX-ACCESS read-write
			STATUS obsolete
			DESCRIPTION
				"Massage is inactive!
				
				Description. Enable/Disable switch for dvbnPlus1ResetFault event"
			::= { dvbnPlus1EventEnableGeneral 1 }

		
		-- 1.3.6.1.4.1.19831.1.1.1.5.6.1.2
		dvbnPlus1RedundancySwitchOverEnable OBJECT-TYPE
			SYNTAX TruthValue
			MAX-ACCESS read-write
			STATUS current
			DESCRIPTION
				"Description. Enable/Disable switch for dvbnPlus1RedundancySwitchOve event"
			::= { dvbnPlus1EventEnableGeneral 2 }

		
		-- 1.3.6.1.4.1.19831.1.1.1.5.6.1.3
		dvbnPlus1LocalModeEnable OBJECT-TYPE
			SYNTAX TruthValue
			MAX-ACCESS read-write
			STATUS current
			DESCRIPTION
				"Description. Enable/Disable switch for dvbnPlus1LocalMode event"
			::= { dvbnPlus1EventEnableGeneral 3 }

		
		-- 1.3.6.1.4.1.19831.1.1.1.5.6.1.4
		dvbnPlus1ControlUnitFaultEnable OBJECT-TYPE
			SYNTAX TruthValue
			MAX-ACCESS read-write
			STATUS current
			DESCRIPTION
				"Description. Enable/Disable switch for dvbnPlus1ControlUnitFault event"
			::= { dvbnPlus1EventEnableGeneral 4 }

		
		-- 1.3.6.1.4.1.19831.1.1.1.5.6.1.5
		dvbnPlus1SwitchOverModeEnable OBJECT-TYPE
			SYNTAX TruthValue
			MAX-ACCESS read-write
			STATUS current
			DESCRIPTION
				"Description. Enable/Disable switch for dvbnPlus1SwitchOverMode event"
			::= { dvbnPlus1EventEnableGeneral 5 }

		
		-- 1.3.6.1.4.1.19831.1.1.1.5.6.1.6
		dvbnPlus1SwitchOverReadyEnable OBJECT-TYPE
			SYNTAX TruthValue
			MAX-ACCESS read-write
			STATUS current
			DESCRIPTION
				"Description. Enable/Disable switch for dvbnPlus1SwitchOverReady event"
			::= { dvbnPlus1EventEnableGeneral 6 }

		
		-- 1.3.6.1.4.1.19831.1.1.1.5.6.1.7
		dvbnPlus1SwitchOverExecutedEnable OBJECT-TYPE
			SYNTAX TruthValue
			MAX-ACCESS read-write
			STATUS current
			DESCRIPTION
				"Description. Enable/Disable switch for dvbnPlus1SwitchOverExecuted event"
			::= { dvbnPlus1EventEnableGeneral 7 }

		
		-- 1.3.6.1.4.1.19831.1.1.1.5.6.1.8
		dvbnPlus1SwitchOverFaultEnable OBJECT-TYPE
			SYNTAX TruthValue
			MAX-ACCESS read-write
			STATUS current
			DESCRIPTION
				"Description. Enable/Disable switch for dvbnPlus1SwitchOverFault event"
			::= { dvbnPlus1EventEnableGeneral 8 }

		
		-- 1.3.6.1.4.1.19831.1.1.1.5.6.1.9
		dvbnPlus1ChannelSelectionEnable OBJECT-TYPE
			SYNTAX TruthValue
			MAX-ACCESS read-write
			STATUS current
			DESCRIPTION
				"Description. Enable/Disable switch for dvbnPlus1ChannelSelection event"
			::= { dvbnPlus1EventEnableGeneral 9 }

		
		-- 1.3.6.1.4.1.19831.1.1.1.5.6.1.10
		dvbnPlus1TransmitterBResetEnable OBJECT-TYPE
			SYNTAX TruthValue
			MAX-ACCESS read-write
			STATUS obsolete
			DESCRIPTION
				"Message is inactive!
				
				Description. Enable/Disable switch for dvbnPlus1TransmitterBReset event"
			::= { dvbnPlus1EventEnableGeneral 10 }

		
		-- 1.3.6.1.4.1.19831.1.1.1.5.6.1.11
		dvbnPlus1TransmitterBModeEnable OBJECT-TYPE
			SYNTAX TruthValue
			MAX-ACCESS read-write
			STATUS obsolete
			DESCRIPTION
				"Message is inactive!
				
				Description. Enable/Disable switch for dvbnPlus1TransmitterBMode event"
			::= { dvbnPlus1EventEnableGeneral 11 }

		
-- dvb N+1 reserve. main transmitter table: events 
		-- 1.3.6.1.4.1.19831.1.1.1.5.6.2
		dvbnPlus1EventEnableMainTransmitterTable OBJECT-TYPE
			SYNTAX SEQUENCE OF DvbnPlus1EventEnableMainTransmitterEntry
			MAX-ACCESS not-accessible
			STATUS current
			DESCRIPTION
				"dvb N+1 reserve. Transmitters main transmitter table: switch for events 
				"
			::= { dvbnPlus1EventEnable 2 }

		
-- dvb N+1 reserve: Main transmitter table rows
		-- 1.3.6.1.4.1.19831.1.1.1.5.6.2.1
		dvbnPlus1EventEnableMainTransmitterEntry OBJECT-TYPE
			SYNTAX DvbnPlus1EventEnableMainTransmitterEntry
			MAX-ACCESS not-accessible
			STATUS current
			DESCRIPTION
				"One logical transmitter, numbered from 1 to n"
			INDEX { dvbnPlus1MTIndex }
			::= { dvbnPlus1EventEnableMainTransmitterTable 1 }

		
		DvbnPlus1EventEnableMainTransmitterEntry ::=
			SEQUENCE { 
				dvbnPlus1MTInputPreselectionEnable
					TruthValue,
				dvbnPlus1MTInputAutomaticEnable
					TruthValue,
				dvbnPlus1MTOpModeEnable
					TruthValue,
				dvbnPlus1MTRFProgramPresentEnable
					TruthValue
			 }

		-- 1.3.6.1.4.1.19831.1.1.1.5.6.2.1.2
		dvbnPlus1MTInputPreselectionEnable OBJECT-TYPE
			SYNTAX TruthValue
			MAX-ACCESS read-write
			STATUS current
			DESCRIPTION
				"Description. Enable/Disable switch for dvbnPlus1MTInputPreselection event"
			::= { dvbnPlus1EventEnableMainTransmitterEntry 2 }

		
		-- 1.3.6.1.4.1.19831.1.1.1.5.6.2.1.3
		dvbnPlus1MTInputAutomaticEnable OBJECT-TYPE
			SYNTAX TruthValue
			MAX-ACCESS read-write
			STATUS current
			DESCRIPTION
				"Description. Enable/Disable switch for dvbnPlus1MTInputAutomatic event"
			::= { dvbnPlus1EventEnableMainTransmitterEntry 3 }

		
		-- 1.3.6.1.4.1.19831.1.1.1.5.6.2.1.4
		dvbnPlus1MTOpModeEnable OBJECT-TYPE
			SYNTAX TruthValue
			MAX-ACCESS read-write
			STATUS current
			DESCRIPTION
				"Description. Enable/Disable switch for dvbnPlus1MTOpMode event"
			::= { dvbnPlus1EventEnableMainTransmitterEntry 4 }

		
		-- 1.3.6.1.4.1.19831.1.1.1.5.6.2.1.5
		dvbnPlus1MTRFProgramPresentEnable OBJECT-TYPE
			SYNTAX TruthValue
			MAX-ACCESS read-write
			STATUS current
			DESCRIPTION
				"Description. Enable/Disable switch for dvbnPlus1MTRFProgramPresent event"
			::= { dvbnPlus1EventEnableMainTransmitterEntry 5 }

		
-- dvb N+1 reserve. reserve transmitter: events
		-- 1.3.6.1.4.1.19831.1.1.1.5.6.3
		dvbnPlus1EventEnableReserveTransmitter OBJECT IDENTIFIER ::= { dvbnPlus1EventEnable 3 }

		
		-- 1.3.6.1.4.1.19831.1.1.1.5.6.3.2
		dvbnPlus1RTInputPreselectionEnable OBJECT-TYPE
			SYNTAX TruthValue
			MAX-ACCESS read-write
			STATUS current
			DESCRIPTION
				"Description. Enable/Disable switch for dvbnPlus1RTInputPreselection event"
			::= { dvbnPlus1EventEnableReserveTransmitter 2 }

		
		-- 1.3.6.1.4.1.19831.1.1.1.5.6.3.3
		dvbnPlus1RTInputAutomaticEnable OBJECT-TYPE
			SYNTAX TruthValue
			MAX-ACCESS read-write
			STATUS current
			DESCRIPTION
				"Description. Enable/Disable switch for dvbnPlus1RTInputAutomatic event"
			::= { dvbnPlus1EventEnableReserveTransmitter 3 }

		
		-- 1.3.6.1.4.1.19831.1.1.1.5.6.3.4
		dvbnPlus1RTOpModeEnable OBJECT-TYPE
			SYNTAX TruthValue
			MAX-ACCESS read-write
			STATUS current
			DESCRIPTION
				"Description. Enable/Disable switch for dvbnPlus1RTOpMode event"
			::= { dvbnPlus1EventEnableReserveTransmitter 4 }

		
		-- 1.3.6.1.4.1.19831.1.1.1.5.6.3.5
		dvbnPlus1RTRFProgramPresentEnable OBJECT-TYPE
			SYNTAX TruthValue
			MAX-ACCESS read-write
			STATUS current
			DESCRIPTION
				"Description. Enable/Disable switch for dvbnPlus1RTRFProgramPresent event"
			::= { dvbnPlus1EventEnableReserveTransmitter 5 }

		
-- N+1 reserve. Transmitters A table: events 
		-- 1.3.6.1.4.1.19831.1.1.1.5.6.4
		dvbnPlus1EventEnableTransmitterATable OBJECT-TYPE
			SYNTAX SEQUENCE OF DvbnPlus1EventEnableTransmitterAEntry
			MAX-ACCESS not-accessible
			STATUS current
			DESCRIPTION
				"n+1 reserve. Transmitters A table: switch for events "
			::= { dvbnPlus1EventEnable 4 }

		
-- dvb N+1 reserve: transmitter A entry - rows
		-- 1.3.6.1.4.1.19831.1.1.1.5.6.4.1
		dvbnPlus1EventEnableTransmitterAEntry OBJECT-TYPE
			SYNTAX DvbnPlus1EventEnableTransmitterAEntry
			MAX-ACCESS not-accessible
			STATUS current
			DESCRIPTION
				"One physical transmitter, numbered from A1 to An"
			INDEX { dvbnPlus1TAIndex }
			::= { dvbnPlus1EventEnableTransmitterATable 1 }

		
		DvbnPlus1EventEnableTransmitterAEntry ::=
			SEQUENCE { 
				dvbnPlus1TARFPresentEnable
					TruthValue,
				dvbnPlus1TAInput1OKEnable
					TruthValue,
				dvbnPlus1TAInput2OKEnable
					TruthValue,
				dvbnPlus1TALocalModeEnable
					TruthValue,
				dvbnPlus1TAInputPreselectionEnable
					TruthValue,
				dvbnPlus1TAInputAutomaticEnable
					TruthValue,
				dvbnPlus1TAFaultEnable
					TruthValue,
				dvbnPlus1TAWarningEnable
					TruthValue,
				dvbnPlus1TAActiveInputEnable
					TruthValue,
				dvbnPlus1TASFNModeEnable
					TruthValue,
				dvbnPlus1TARefFaultEnable
					TruthValue,
				dvbnPlus1TAMuteEnable
					TruthValue,
				dvbnPlus1TAFaultMIPEnable
					TruthValue,
				dvbnPlus1TAStuffingModeEnable
					TruthValue
			 }

		-- 1.3.6.1.4.1.19831.1.1.1.5.6.4.1.2
		dvbnPlus1TARFPresentEnable OBJECT-TYPE
			SYNTAX TruthValue
			MAX-ACCESS read-write
			STATUS current
			DESCRIPTION
				"Description. Enable/Disable switch for dvbnPlus1TARFPresent event"
			::= { dvbnPlus1EventEnableTransmitterAEntry 2 }

		
		-- 1.3.6.1.4.1.19831.1.1.1.5.6.4.1.3
		dvbnPlus1TAInput1OKEnable OBJECT-TYPE
			SYNTAX TruthValue
			MAX-ACCESS read-write
			STATUS current
			DESCRIPTION
				"Description. Enable/Disable switch for dvbnPlus1TAInput1OK event"
			::= { dvbnPlus1EventEnableTransmitterAEntry 3 }

		
		-- 1.3.6.1.4.1.19831.1.1.1.5.6.4.1.4
		dvbnPlus1TAInput2OKEnable OBJECT-TYPE
			SYNTAX TruthValue
			MAX-ACCESS read-write
			STATUS current
			DESCRIPTION
				"Description. Enable/Disable switch for dvbnPlus1TAInput2OK event"
			::= { dvbnPlus1EventEnableTransmitterAEntry 4 }

		
		-- 1.3.6.1.4.1.19831.1.1.1.5.6.4.1.5
		dvbnPlus1TALocalModeEnable OBJECT-TYPE
			SYNTAX TruthValue
			MAX-ACCESS read-write
			STATUS current
			DESCRIPTION
				"Description. Enable/Disable switch for dvbnPlus1TALocalMode event"
			::= { dvbnPlus1EventEnableTransmitterAEntry 5 }

		
		-- 1.3.6.1.4.1.19831.1.1.1.5.6.4.1.6
		dvbnPlus1TAInputPreselectionEnable OBJECT-TYPE
			SYNTAX TruthValue
			MAX-ACCESS read-write
			STATUS current
			DESCRIPTION
				"Description. Enable/Disable switch for dvbnPlus1TAInputPreselection event"
			::= { dvbnPlus1EventEnableTransmitterAEntry 6 }

		
		-- 1.3.6.1.4.1.19831.1.1.1.5.6.4.1.7
		dvbnPlus1TAInputAutomaticEnable OBJECT-TYPE
			SYNTAX TruthValue
			MAX-ACCESS read-write
			STATUS current
			DESCRIPTION
				"Description. Enable/Disable switch for dvbnPlus1TAInputAutomatic event"
			::= { dvbnPlus1EventEnableTransmitterAEntry 7 }

		
		-- 1.3.6.1.4.1.19831.1.1.1.5.6.4.1.8
		dvbnPlus1TAFaultEnable OBJECT-TYPE
			SYNTAX TruthValue
			MAX-ACCESS read-write
			STATUS current
			DESCRIPTION
				"Description. Enable/Disable switch for dvbnPlus1TAFault event"
			::= { dvbnPlus1EventEnableTransmitterAEntry 8 }

		
		-- 1.3.6.1.4.1.19831.1.1.1.5.6.4.1.9
		dvbnPlus1TAWarningEnable OBJECT-TYPE
			SYNTAX TruthValue
			MAX-ACCESS read-write
			STATUS current
			DESCRIPTION
				"Description. Enable/Disable switch for dvbnPlus1TAWarning event"
			::= { dvbnPlus1EventEnableTransmitterAEntry 9 }

		
		-- 1.3.6.1.4.1.19831.1.1.1.5.6.4.1.10
		dvbnPlus1TAActiveInputEnable OBJECT-TYPE
			SYNTAX TruthValue
			MAX-ACCESS read-write
			STATUS current
			DESCRIPTION
				"Description. Enable/Disable switch for dvbnPlus1TAActiveInput event"
			::= { dvbnPlus1EventEnableTransmitterAEntry 10 }

		
		-- 1.3.6.1.4.1.19831.1.1.1.5.6.4.1.11
		dvbnPlus1TASFNModeEnable OBJECT-TYPE
			SYNTAX TruthValue
			MAX-ACCESS read-write
			STATUS current
			DESCRIPTION
				"Description. Enable/Disable switch for dvbnPlus1TASFNMode event"
			::= { dvbnPlus1EventEnableTransmitterAEntry 11 }

		
		-- 1.3.6.1.4.1.19831.1.1.1.5.6.4.1.12
		dvbnPlus1TARefFaultEnable OBJECT-TYPE
			SYNTAX TruthValue
			MAX-ACCESS read-write
			STATUS current
			DESCRIPTION
				"Description. Enable/Disable switch for dvbnPlus1TARefFault event"
			::= { dvbnPlus1EventEnableTransmitterAEntry 12 }

		
		-- 1.3.6.1.4.1.19831.1.1.1.5.6.4.1.13
		dvbnPlus1TAMuteEnable OBJECT-TYPE
			SYNTAX TruthValue
			MAX-ACCESS read-write
			STATUS current
			DESCRIPTION
				"Description. Enable/Disable switch for dvbnPlus1TAMute event"
			::= { dvbnPlus1EventEnableTransmitterAEntry 13 }

		
		-- 1.3.6.1.4.1.19831.1.1.1.5.6.4.1.14
		dvbnPlus1TAFaultMIPEnable OBJECT-TYPE
			SYNTAX TruthValue
			MAX-ACCESS read-write
			STATUS current
			DESCRIPTION
				"Description. Enable/Disable switch for dvbnPlus1TAFaultMIP event"
			::= { dvbnPlus1EventEnableTransmitterAEntry 14 }

		
		-- 1.3.6.1.4.1.19831.1.1.1.5.6.4.1.15
		dvbnPlus1TAStuffingModeEnable OBJECT-TYPE
			SYNTAX TruthValue
			MAX-ACCESS read-write
			STATUS current
			DESCRIPTION
				"Description. Enable/Disable switch for dvbnPlus1TAStuffingMode event"
			::= { dvbnPlus1EventEnableTransmitterAEntry 15 }

		
-- dvb N+1: transmitter B: events
		-- 1.3.6.1.4.1.19831.1.1.1.5.6.5
		dvbnPlus1EventEnableTransmitterB OBJECT IDENTIFIER ::= { dvbnPlus1EventEnable 5 }

		
		-- 1.3.6.1.4.1.19831.1.1.1.5.6.5.2
		dvbnPlus1TBRFPresentEnable OBJECT-TYPE
			SYNTAX TruthValue
			MAX-ACCESS read-write
			STATUS current
			DESCRIPTION
				"Description. Enable/Disable switch for dvbnPlus1TBRFPresent event"
			::= { dvbnPlus1EventEnableTransmitterB 2 }

		
		-- 1.3.6.1.4.1.19831.1.1.1.5.6.5.3
		dvbnPlus1TBInput1OKEnable OBJECT-TYPE
			SYNTAX TruthValue
			MAX-ACCESS read-write
			STATUS current
			DESCRIPTION
				"Description. Enable/Disable switch for dvbnPlus1TBInput1OK event"
			::= { dvbnPlus1EventEnableTransmitterB 3 }

		
		-- 1.3.6.1.4.1.19831.1.1.1.5.6.5.4
		dvbnPlus1TBInput2OKEnable OBJECT-TYPE
			SYNTAX TruthValue
			MAX-ACCESS read-write
			STATUS current
			DESCRIPTION
				"Description. Enable/Disable switch for dvbnPlus1TBInput2OK event"
			::= { dvbnPlus1EventEnableTransmitterB 4 }

		
		-- 1.3.6.1.4.1.19831.1.1.1.5.6.5.5
		dvbnPlus1TBLocalModeEnable OBJECT-TYPE
			SYNTAX TruthValue
			MAX-ACCESS read-write
			STATUS current
			DESCRIPTION
				"Description. Enable/Disable switch for dvbnPlus1TBLocalMode event"
			::= { dvbnPlus1EventEnableTransmitterB 5 }

		
		-- 1.3.6.1.4.1.19831.1.1.1.5.6.5.6
		dvbnPlus1TBFaultEnable OBJECT-TYPE
			SYNTAX TruthValue
			MAX-ACCESS read-write
			STATUS current
			DESCRIPTION
				"Description. Enable/Disable switch for dvbnPlus1TBFault event"
			::= { dvbnPlus1EventEnableTransmitterB 6 }

		
		-- 1.3.6.1.4.1.19831.1.1.1.5.6.5.7
		dvbnPlus1TBWarningEnable OBJECT-TYPE
			SYNTAX TruthValue
			MAX-ACCESS read-write
			STATUS current
			DESCRIPTION
				"Description. Enable/Disable switch for dvbnPlus1TBWarning event"
			::= { dvbnPlus1EventEnableTransmitterB 7 }

		
		-- 1.3.6.1.4.1.19831.1.1.1.5.6.5.8
		dvbnPlus1TBInputPreselectionEnable OBJECT-TYPE
			SYNTAX TruthValue
			MAX-ACCESS read-write
			STATUS current
			DESCRIPTION
				"Description. Enable/Disable switch for dvbnPlus1TBInputPreselection event"
			::= { dvbnPlus1EventEnableTransmitterB 8 }

		
		-- 1.3.6.1.4.1.19831.1.1.1.5.6.5.9
		dvbnPlus1TBInputAutomaticEnable OBJECT-TYPE
			SYNTAX TruthValue
			MAX-ACCESS read-write
			STATUS current
			DESCRIPTION
				"Description. Enable/Disable switch for dvbnPlus1TBInputAutomatic event"
			::= { dvbnPlus1EventEnableTransmitterB 9 }

		
		-- 1.3.6.1.4.1.19831.1.1.1.5.6.5.10
		dvbnPlus1TBActiveInputEnable OBJECT-TYPE
			SYNTAX TruthValue
			MAX-ACCESS read-write
			STATUS current
			DESCRIPTION
				"Description. Enable/Disable switch for dvbnPlus1TBActiveInput event"
			::= { dvbnPlus1EventEnableTransmitterB 10 }

		
		-- 1.3.6.1.4.1.19831.1.1.1.5.6.5.11
		dvbnPlus1TBSFNModeEnable OBJECT-TYPE
			SYNTAX TruthValue
			MAX-ACCESS read-write
			STATUS current
			DESCRIPTION
				"Description. Enable/Disable switch for dvbnPlus1TBSFNMode event"
			::= { dvbnPlus1EventEnableTransmitterB 11 }

		
		-- 1.3.6.1.4.1.19831.1.1.1.5.6.5.12
		dvbnPlus1TBRefFaultEnable OBJECT-TYPE
			SYNTAX TruthValue
			MAX-ACCESS read-write
			STATUS current
			DESCRIPTION
				"Description. Enable/Disable switch for dvbnPlus1TBRefFault event"
			::= { dvbnPlus1EventEnableTransmitterB 12 }

		
		-- 1.3.6.1.4.1.19831.1.1.1.5.6.5.13
		dvbnPlus1TBMuteEnable OBJECT-TYPE
			SYNTAX TruthValue
			MAX-ACCESS read-write
			STATUS current
			DESCRIPTION
				"Description. Enable/Disable switch for dvbnPlus1TBMute event"
			::= { dvbnPlus1EventEnableTransmitterB 13 }

		
		-- 1.3.6.1.4.1.19831.1.1.1.5.6.5.14
		dvbnPlus1TBFaultMIPEnable OBJECT-TYPE
			SYNTAX TruthValue
			MAX-ACCESS read-write
			STATUS current
			DESCRIPTION
				"Description. Enable/Disable switch for dvbnPlus1TBFaultMIP event"
			::= { dvbnPlus1EventEnableTransmitterB 14 }

		
		-- 1.3.6.1.4.1.19831.1.1.1.5.6.5.15
		dvbnPlus1TBStuffingModeEnable OBJECT-TYPE
			SYNTAX TruthValue
			MAX-ACCESS read-write
			STATUS current
			DESCRIPTION
				"Description. Enable/Disable switch for dvbnPlus1TBStuffingMode event"
			::= { dvbnPlus1EventEnableTransmitterB 15 }

		
-- dvb N+1 reserve. Event priority
		-- 1.3.6.1.4.1.19831.1.1.1.5.7
		dvbnPlus1EventPriority OBJECT IDENTIFIER ::= { dvbnPlus1 7 }

		
-- dvb N+1 reserve: general: event priority
		-- 1.3.6.1.4.1.19831.1.1.1.5.7.1
		dvbnPlus1EventPriorityGeneral OBJECT IDENTIFIER ::= { dvbnPlus1EventPriority 1 }

		
		-- 1.3.6.1.4.1.19831.1.1.1.5.7.1.1
		dvbnPlus1ResetFaultPriority OBJECT-TYPE
			SYNTAX Unsigned32
			MAX-ACCESS read-write
			STATUS obsolete
			DESCRIPTION
				"Massage is inactive!
				
				Description. Priority switch for dvbnPlus1ResetFault event"
			::= { dvbnPlus1EventPriorityGeneral 1 }

		
		-- 1.3.6.1.4.1.19831.1.1.1.5.7.1.2
		dvbnPlus1RedundancySwitchOverPriority OBJECT-TYPE
			SYNTAX Unsigned32
			MAX-ACCESS read-write
			STATUS current
			DESCRIPTION
				"Priority switch for dvbnPlus1RedundancySwitchOver event"
			::= { dvbnPlus1EventPriorityGeneral 2 }

		
		-- 1.3.6.1.4.1.19831.1.1.1.5.7.1.3
		dvbnPlus1LocalModePriority OBJECT-TYPE
			SYNTAX Unsigned32
			MAX-ACCESS read-write
			STATUS current
			DESCRIPTION
				"Priority switch for dvbnPlus1LocalMode event"
			::= { dvbnPlus1EventPriorityGeneral 3 }

		
		-- 1.3.6.1.4.1.19831.1.1.1.5.7.1.4
		dvbnPlus1ControlUnitFaultPriority OBJECT-TYPE
			SYNTAX Unsigned32
			MAX-ACCESS read-write
			STATUS current
			DESCRIPTION
				"Priority switch for dvbnPlus1ControlUnitFault event"
			::= { dvbnPlus1EventPriorityGeneral 4 }

		
		-- 1.3.6.1.4.1.19831.1.1.1.5.7.1.5
		dvbnPlus1SwitchOverModePriority OBJECT-TYPE
			SYNTAX Unsigned32
			MAX-ACCESS read-write
			STATUS current
			DESCRIPTION
				"Priority switch for dvbnPlus1SwitchOverMode event"
			::= { dvbnPlus1EventPriorityGeneral 5 }

		
		-- 1.3.6.1.4.1.19831.1.1.1.5.7.1.6
		dvbnPlus1SwitchOverReadyPriority OBJECT-TYPE
			SYNTAX Unsigned32
			MAX-ACCESS read-write
			STATUS current
			DESCRIPTION
				"Priority switch for dvbnPlus1SwitchOverReady event"
			::= { dvbnPlus1EventPriorityGeneral 6 }

		
		-- 1.3.6.1.4.1.19831.1.1.1.5.7.1.7
		dvbnPlus1SwitchOverExecutedPriority OBJECT-TYPE
			SYNTAX Unsigned32
			MAX-ACCESS read-write
			STATUS current
			DESCRIPTION
				"Priority switch for dvbnPlus1SwitchOverExecuted event"
			::= { dvbnPlus1EventPriorityGeneral 7 }

		
		-- 1.3.6.1.4.1.19831.1.1.1.5.7.1.8
		dvbnPlus1SwitchOverFaultPriority OBJECT-TYPE
			SYNTAX Unsigned32
			MAX-ACCESS read-write
			STATUS current
			DESCRIPTION
				"Priority switch for dvbnPlus1SwitchOverFault event"
			::= { dvbnPlus1EventPriorityGeneral 8 }

		
		-- 1.3.6.1.4.1.19831.1.1.1.5.7.1.9
		dvbnPlus1ChannelSelectionPriority OBJECT-TYPE
			SYNTAX Unsigned32
			MAX-ACCESS read-write
			STATUS current
			DESCRIPTION
				"Priority switch for dvbnPlus1RChanelSelection event"
			::= { dvbnPlus1EventPriorityGeneral 9 }

		
		-- 1.3.6.1.4.1.19831.1.1.1.5.7.1.10
		dvbnPlus1TransmitterBResetPriority OBJECT-TYPE
			SYNTAX Unsigned32
			MAX-ACCESS read-write
			STATUS obsolete
			DESCRIPTION
				"Message is inactive!
				
				Priority switch for dvbnPlus1TransmitterBReset event"
			::= { dvbnPlus1EventPriorityGeneral 10 }

		
		-- 1.3.6.1.4.1.19831.1.1.1.5.7.1.11
		dvbnPlus1TransmitterBModePriority OBJECT-TYPE
			SYNTAX Unsigned32
			MAX-ACCESS read-write
			STATUS obsolete
			DESCRIPTION
				"Message is inactive!
				
				Priority switch for dvbnPlus1TransmitterBMode event"
			::= { dvbnPlus1EventPriorityGeneral 11 }

		
-- dvb N+1 reserve: Main transmitter table: event priority
		-- 1.3.6.1.4.1.19831.1.1.1.5.7.2
		dvbnPlus1EventPriorityMainTransmitterTable OBJECT-TYPE
			SYNTAX SEQUENCE OF DvbnPlus1EventPriorityMainTransmitterEntry
			MAX-ACCESS not-accessible
			STATUS current
			DESCRIPTION
				"dvb n+1 reserve. general: priority for event"
			::= { dvbnPlus1EventPriority 2 }

		
-- dvb N+1 reserve: Main transmitter table rows
		-- 1.3.6.1.4.1.19831.1.1.1.5.7.2.1
		dvbnPlus1EventPriorityMainTransmitterEntry OBJECT-TYPE
			SYNTAX DvbnPlus1EventPriorityMainTransmitterEntry
			MAX-ACCESS not-accessible
			STATUS current
			DESCRIPTION
				"One logical transmitter, numbered from 1 to n"
			INDEX { dvbnPlus1MTIndex }
			::= { dvbnPlus1EventPriorityMainTransmitterTable 1 }

		
		DvbnPlus1EventPriorityMainTransmitterEntry ::=
			SEQUENCE { 
				dvbnPlus1MTInputPreselectionPriority
					Unsigned32,
				dvbnPlus1MTInputAutomaticPriority
					Unsigned32,
				dvbnPlus1MTOpModePriority
					Unsigned32,
				dvbnPlus1MTRFProgramPresentPriority
					Unsigned32
			 }

		-- 1.3.6.1.4.1.19831.1.1.1.5.7.2.1.2
		dvbnPlus1MTInputPreselectionPriority OBJECT-TYPE
			SYNTAX Unsigned32
			MAX-ACCESS read-write
			STATUS current
			DESCRIPTION
				"Priority switch for dvbnPlus1MTInputPreselection event"
			::= { dvbnPlus1EventPriorityMainTransmitterEntry 2 }

		
		-- 1.3.6.1.4.1.19831.1.1.1.5.7.2.1.3
		dvbnPlus1MTInputAutomaticPriority OBJECT-TYPE
			SYNTAX Unsigned32
			MAX-ACCESS read-write
			STATUS current
			DESCRIPTION
				"Priority switch for dvbnPlus1MTInputAutomatic event"
			::= { dvbnPlus1EventPriorityMainTransmitterEntry 3 }

		
		-- 1.3.6.1.4.1.19831.1.1.1.5.7.2.1.4
		dvbnPlus1MTOpModePriority OBJECT-TYPE
			SYNTAX Unsigned32
			MAX-ACCESS read-write
			STATUS current
			DESCRIPTION
				"Priority switch for dvbnPlus1MTTransmitterOpMode event"
			::= { dvbnPlus1EventPriorityMainTransmitterEntry 4 }

		
		-- 1.3.6.1.4.1.19831.1.1.1.5.7.2.1.5
		dvbnPlus1MTRFProgramPresentPriority OBJECT-TYPE
			SYNTAX Unsigned32
			MAX-ACCESS read-write
			STATUS current
			DESCRIPTION
				"Priority switch for dvbnPlus1MTRFProgramPresent event"
			::= { dvbnPlus1EventPriorityMainTransmitterEntry 5 }

		
-- dvb N+1 reserve. Reserve transmitter: event priority
		-- 1.3.6.1.4.1.19831.1.1.1.5.7.3
		dvbnPlus1EventPriorityReserveTransmitter OBJECT IDENTIFIER ::= { dvbnPlus1EventPriority 3 }

		
		-- 1.3.6.1.4.1.19831.1.1.1.5.7.3.2
		dvbnPlus1RTInputPreselectionPriority OBJECT-TYPE
			SYNTAX Unsigned32
			MAX-ACCESS read-write
			STATUS current
			DESCRIPTION
				"Priority switch for dvbnPlus1RTInputPreselection event"
			::= { dvbnPlus1EventPriorityReserveTransmitter 2 }

		
		-- 1.3.6.1.4.1.19831.1.1.1.5.7.3.3
		dvbnPlus1RTInputAutomaticPriority OBJECT-TYPE
			SYNTAX Unsigned32
			MAX-ACCESS read-write
			STATUS current
			DESCRIPTION
				"Priority switch for dvbnPlus1RTInputAutomatic event"
			::= { dvbnPlus1EventPriorityReserveTransmitter 3 }

		
		-- 1.3.6.1.4.1.19831.1.1.1.5.7.3.4
		dvbnPlus1RTOpModePriority OBJECT-TYPE
			SYNTAX Unsigned32
			MAX-ACCESS read-write
			STATUS current
			DESCRIPTION
				"Priority switch for dvbnPlus1RTOpMode event"
			::= { dvbnPlus1EventPriorityReserveTransmitter 4 }

		
		-- 1.3.6.1.4.1.19831.1.1.1.5.7.3.5
		dvbnPlus1RTRFProgramPresentPriority OBJECT-TYPE
			SYNTAX Unsigned32
			MAX-ACCESS read-write
			STATUS current
			DESCRIPTION
				"Priority switch for dvbnPlus1RTRFProgramPresent event"
			::= { dvbnPlus1EventPriorityReserveTransmitter 5 }

		
-- dvb N+1 reserve. Transmitter A table: event priority
		-- 1.3.6.1.4.1.19831.1.1.1.5.7.4
		dvbnPlus1EventPriorityTransmitterATable OBJECT-TYPE
			SYNTAX SEQUENCE OF DvbnPlus1EventPriorityTransmitterAEntry
			MAX-ACCESS not-accessible
			STATUS current
			DESCRIPTION
				"dvb n+1 reserve. transmitter A table: priority for event"
			::= { dvbnPlus1EventPriority 4 }

		
-- dvb N+1 reserve. Transmitter A entry - rows
		-- 1.3.6.1.4.1.19831.1.1.1.5.7.4.1
		dvbnPlus1EventPriorityTransmitterAEntry OBJECT-TYPE
			SYNTAX DvbnPlus1EventPriorityTransmitterAEntry
			MAX-ACCESS not-accessible
			STATUS current
			DESCRIPTION
				"One physical transmitter, numbered from A1 to An"
			INDEX { dvbnPlus1TAIndex }
			::= { dvbnPlus1EventPriorityTransmitterATable 1 }

		
		DvbnPlus1EventPriorityTransmitterAEntry ::=
			SEQUENCE { 
				dvbnPlus1TARFPresentPriority
					Unsigned32,
				dvbnPlus1TAInput1OKPriority
					Unsigned32,
				dvbnPlus1TAInput2OKPriority
					Unsigned32,
				dvbnPlus1TALocalModePriority
					Unsigned32,
				dvbnPlus1TAInputPreselectionPriority
					Unsigned32,
				dvbnPlus1TAInputAutomaticPriority
					Unsigned32,
				dvbnPlus1TAFaultPriority
					Unsigned32,
				dvbnPlus1TAWarningPriority
					Unsigned32,
				dvbnPlus1TAActiveInputPriority
					Unsigned32,
				dvbnPlus1TASFNModePriority
					Unsigned32,
				dvbnPlus1TARefFaultPriority
					Unsigned32,
				dvbnPlus1TAMutePriority
					Unsigned32,
				dvbnPlus1TAFaultMIPPriority
					Unsigned32,
				dvbnPlus1TAStuffingModePriority
					Unsigned32
			 }

		-- 1.3.6.1.4.1.19831.1.1.1.5.7.4.1.2
		dvbnPlus1TARFPresentPriority OBJECT-TYPE
			SYNTAX Unsigned32
			MAX-ACCESS read-write
			STATUS current
			DESCRIPTION
				"Priority switch for dvbnPlus1TARFPresent event"
			::= { dvbnPlus1EventPriorityTransmitterAEntry 2 }

		
		-- 1.3.6.1.4.1.19831.1.1.1.5.7.4.1.3
		dvbnPlus1TAInput1OKPriority OBJECT-TYPE
			SYNTAX Unsigned32
			MAX-ACCESS read-write
			STATUS current
			DESCRIPTION
				"Priority switch for dvbnPlus1TAInput1OK event"
			::= { dvbnPlus1EventPriorityTransmitterAEntry 3 }

		
		-- 1.3.6.1.4.1.19831.1.1.1.5.7.4.1.4
		dvbnPlus1TAInput2OKPriority OBJECT-TYPE
			SYNTAX Unsigned32
			MAX-ACCESS read-write
			STATUS current
			DESCRIPTION
				"Priority switch for dvbnPlus1TAInput2OK event"
			::= { dvbnPlus1EventPriorityTransmitterAEntry 4 }

		
		-- 1.3.6.1.4.1.19831.1.1.1.5.7.4.1.5
		dvbnPlus1TALocalModePriority OBJECT-TYPE
			SYNTAX Unsigned32
			MAX-ACCESS read-write
			STATUS current
			DESCRIPTION
				"Priority switch for dvbnPlus1TALocalModer event"
			::= { dvbnPlus1EventPriorityTransmitterAEntry 5 }

		
		-- 1.3.6.1.4.1.19831.1.1.1.5.7.4.1.6
		dvbnPlus1TAInputPreselectionPriority OBJECT-TYPE
			SYNTAX Unsigned32
			MAX-ACCESS read-write
			STATUS current
			DESCRIPTION
				"Priority switch for dvbnPlus1TAInputPreselection event"
			::= { dvbnPlus1EventPriorityTransmitterAEntry 6 }

		
		-- 1.3.6.1.4.1.19831.1.1.1.5.7.4.1.7
		dvbnPlus1TAInputAutomaticPriority OBJECT-TYPE
			SYNTAX Unsigned32
			MAX-ACCESS read-write
			STATUS current
			DESCRIPTION
				"Priority switch for dvbnPlus1TAInputAutomatic event"
			::= { dvbnPlus1EventPriorityTransmitterAEntry 7 }

		
		-- 1.3.6.1.4.1.19831.1.1.1.5.7.4.1.8
		dvbnPlus1TAFaultPriority OBJECT-TYPE
			SYNTAX Unsigned32
			MAX-ACCESS read-write
			STATUS current
			DESCRIPTION
				"Priority switch for dvbnPlus1TAFaultPriority event"
			::= { dvbnPlus1EventPriorityTransmitterAEntry 8 }

		
		-- 1.3.6.1.4.1.19831.1.1.1.5.7.4.1.9
		dvbnPlus1TAWarningPriority OBJECT-TYPE
			SYNTAX Unsigned32
			MAX-ACCESS read-write
			STATUS current
			DESCRIPTION
				"Priority switch for dvbnPlus1TAWarning event"
			::= { dvbnPlus1EventPriorityTransmitterAEntry 9 }

		
		-- 1.3.6.1.4.1.19831.1.1.1.5.7.4.1.10
		dvbnPlus1TAActiveInputPriority OBJECT-TYPE
			SYNTAX Unsigned32
			MAX-ACCESS read-write
			STATUS current
			DESCRIPTION
				"Priority switch for dvbnPlus1TAActiveInput event"
			::= { dvbnPlus1EventPriorityTransmitterAEntry 10 }

		
		-- 1.3.6.1.4.1.19831.1.1.1.5.7.4.1.11
		dvbnPlus1TASFNModePriority OBJECT-TYPE
			SYNTAX Unsigned32
			MAX-ACCESS read-write
			STATUS current
			DESCRIPTION
				"Priority switch for dvbnPlus1TASFNMode event"
			::= { dvbnPlus1EventPriorityTransmitterAEntry 11 }

		
		-- 1.3.6.1.4.1.19831.1.1.1.5.7.4.1.12
		dvbnPlus1TARefFaultPriority OBJECT-TYPE
			SYNTAX Unsigned32
			MAX-ACCESS read-write
			STATUS current
			DESCRIPTION
				"Priority switch for dvbnPlus1TARefFault event"
			::= { dvbnPlus1EventPriorityTransmitterAEntry 12 }

		
		-- 1.3.6.1.4.1.19831.1.1.1.5.7.4.1.13
		dvbnPlus1TAMutePriority OBJECT-TYPE
			SYNTAX Unsigned32
			MAX-ACCESS read-write
			STATUS current
			DESCRIPTION
				"Priority switch for dvbnPlus1TAMute event"
			::= { dvbnPlus1EventPriorityTransmitterAEntry 13 }

		
		-- 1.3.6.1.4.1.19831.1.1.1.5.7.4.1.14
		dvbnPlus1TAFaultMIPPriority OBJECT-TYPE
			SYNTAX Unsigned32
			MAX-ACCESS read-write
			STATUS current
			DESCRIPTION
				"Priority switch for dvbnPlus1TAFaultMIP event"
			::= { dvbnPlus1EventPriorityTransmitterAEntry 14 }

		
		-- 1.3.6.1.4.1.19831.1.1.1.5.7.4.1.15
		dvbnPlus1TAStuffingModePriority OBJECT-TYPE
			SYNTAX Unsigned32
			MAX-ACCESS read-write
			STATUS current
			DESCRIPTION
				"Priority switch for dvbnPlus1TAStuffingMode event"
			::= { dvbnPlus1EventPriorityTransmitterAEntry 15 }

		
-- dvb N+1. Tansmitter B event priority
		-- 1.3.6.1.4.1.19831.1.1.1.5.7.5
		dvbnPlus1EventPriorityTransmitterB OBJECT IDENTIFIER ::= { dvbnPlus1EventPriority 5 }

		
		-- 1.3.6.1.4.1.19831.1.1.1.5.7.5.2
		dvbnPlus1TBRFPresentPriority OBJECT-TYPE
			SYNTAX Unsigned32
			MAX-ACCESS read-write
			STATUS current
			DESCRIPTION
				"Priority switch for dvbnPlus1TBRFPresent event"
			::= { dvbnPlus1EventPriorityTransmitterB 2 }

		
		-- 1.3.6.1.4.1.19831.1.1.1.5.7.5.3
		dvbnPlus1TBInput1OKPriority OBJECT-TYPE
			SYNTAX Unsigned32
			MAX-ACCESS read-write
			STATUS current
			DESCRIPTION
				"Priority switch for dvbnPlus1TBInput1OK event"
			::= { dvbnPlus1EventPriorityTransmitterB 3 }

		
		-- 1.3.6.1.4.1.19831.1.1.1.5.7.5.4
		dvbnPlus1TBInput2OKPriority OBJECT-TYPE
			SYNTAX Unsigned32
			MAX-ACCESS read-write
			STATUS current
			DESCRIPTION
				"Priority switch for dvbnPlus1TBInput2OK event"
			::= { dvbnPlus1EventPriorityTransmitterB 4 }

		
		-- 1.3.6.1.4.1.19831.1.1.1.5.7.5.5
		dvbnPlus1TBLocalModePriority OBJECT-TYPE
			SYNTAX Unsigned32
			MAX-ACCESS read-write
			STATUS current
			DESCRIPTION
				"Priority switch for dvbnPlus1TBLocalMode event"
			::= { dvbnPlus1EventPriorityTransmitterB 5 }

		
		-- 1.3.6.1.4.1.19831.1.1.1.5.7.5.6
		dvbnPlus1TBFaultPriority OBJECT-TYPE
			SYNTAX Unsigned32
			MAX-ACCESS read-write
			STATUS current
			DESCRIPTION
				"Priority switch for dvbnPlus1TBFault event"
			::= { dvbnPlus1EventPriorityTransmitterB 6 }

		
		-- 1.3.6.1.4.1.19831.1.1.1.5.7.5.7
		dvbnPlus1TBWarningPriority OBJECT-TYPE
			SYNTAX Unsigned32
			MAX-ACCESS read-write
			STATUS current
			DESCRIPTION
				"Priority switch for dvbnPlus1TBWarning event"
			::= { dvbnPlus1EventPriorityTransmitterB 7 }

		
		-- 1.3.6.1.4.1.19831.1.1.1.5.7.5.8
		dvbnPlus1TBInputPreselectionPriority OBJECT-TYPE
			SYNTAX Unsigned32
			MAX-ACCESS read-write
			STATUS current
			DESCRIPTION
				"Priority switch for dvbnPlus1TBInputPreselection event"
			::= { dvbnPlus1EventPriorityTransmitterB 8 }

		
		-- 1.3.6.1.4.1.19831.1.1.1.5.7.5.9
		dvbnPlus1TBInputAutomaticPriority OBJECT-TYPE
			SYNTAX Unsigned32
			MAX-ACCESS read-write
			STATUS current
			DESCRIPTION
				"Priority switch for dvbnPlus1TBInputAutomatic event"
			::= { dvbnPlus1EventPriorityTransmitterB 9 }

		
		-- 1.3.6.1.4.1.19831.1.1.1.5.7.5.10
		dvbnPlus1TBActiveInputPriority OBJECT-TYPE
			SYNTAX Unsigned32
			MAX-ACCESS read-write
			STATUS current
			DESCRIPTION
				"Priority switch for dvbnPlus1TBActiveInput event"
			::= { dvbnPlus1EventPriorityTransmitterB 10 }

		
		-- 1.3.6.1.4.1.19831.1.1.1.5.7.5.11
		dvbnPlus1TBSFNModePriority OBJECT-TYPE
			SYNTAX Unsigned32
			MAX-ACCESS read-write
			STATUS current
			DESCRIPTION
				"NPriority switch for dvbnPlus1TBSFNMode event"
			::= { dvbnPlus1EventPriorityTransmitterB 11 }

		
		-- 1.3.6.1.4.1.19831.1.1.1.5.7.5.12
		dvbnPlus1TBRefFaultPriority OBJECT-TYPE
			SYNTAX Unsigned32
			MAX-ACCESS read-write
			STATUS current
			DESCRIPTION
				"Priority switch for dvbnPlus1TBRefFault event"
			::= { dvbnPlus1EventPriorityTransmitterB 12 }

		
		-- 1.3.6.1.4.1.19831.1.1.1.5.7.5.13
		dvbnPlus1TBMutePriority OBJECT-TYPE
			SYNTAX Unsigned32
			MAX-ACCESS read-write
			STATUS current
			DESCRIPTION
				"Priority switch for dvbnPlus1TBMute event"
			::= { dvbnPlus1EventPriorityTransmitterB 13 }

		
		-- 1.3.6.1.4.1.19831.1.1.1.5.7.5.14
		dvbnPlus1TBFaultMIPPriority OBJECT-TYPE
			SYNTAX Unsigned32
			MAX-ACCESS read-write
			STATUS current
			DESCRIPTION
				"Priority switch for dvbnPlus1TBFaultMIP event"
			::= { dvbnPlus1EventPriorityTransmitterB 14 }

		
		-- 1.3.6.1.4.1.19831.1.1.1.5.7.5.15
		dvbnPlus1TBStuffingModePriority OBJECT-TYPE
			SYNTAX Unsigned32
			MAX-ACCESS read-write
			STATUS current
			DESCRIPTION
				"Priority switch for dvbnPlus1TBStuffingMode event"
			::= { dvbnPlus1EventPriorityTransmitterB 15 }

		
		-- 1.3.6.1.4.1.19831.1.1.1.5.8
		groupsnPlus1 OBJECT IDENTIFIER ::= { dvbnPlus1 8 }

		
		-- 1.3.6.1.4.1.19831.1.1.1.5.8.1
		objectGroupnPlus1 OBJECT-GROUP
			OBJECTS { dvbnPlus1RedundancySwitchOver, dvbnPlus1MTRFProgramPresent, dvbnPlus1RTRFProgramPresent, dvbnPlus1RedundancySwitchOverEnable, dvbnPlus1RedundancySwitchOverPriority, 
				dvbnPlus1RTInputPreselectionEnable, dvbnPlus1TBFaultMIPPriority, dvbnPlus1TBStuffingModePriority, dvbnPlus1EventTransmitterIndex, dvbnPlus1RTInputPreselection, 
				dvbnPlus1LocalMode, dvbnPlus1ControlUnitFault, dvbnPlus1SwitchOverMode, dvbnPlus1SwitchOverReady, dvbnPlus1SwitchOverExecuted, 
				dvbnPlus1SwitchOverFault, dvbnPlus1ChannelSelection, dvbnPlus1MTIndex, dvbnPlus1MTInputPreselection, dvbnPlus1MTInputAutomatic, 
				dvbnPlus1RTInputAutomatic, dvbnPlus1RTOpMode, dvbnPlus1TAIndex, dvbnPlus1TARFPresent, dvbnPlus1TAInput1OK, 
				dvbnPlus1TAInput2OK, dvbnPlus1TALocalMode, dvbnPlus1TAInputPreselection, dvbnPlus1TAInputAutomatic, dvbnPlus1TAFault, 
				dvbnPlus1TAWarning, dvbnPlus1TAActiveInput, dvbnPlus1TASFNMode, dvbnPlus1TARefFault, dvbnPlus1TAMute, 
				dvbnPlus1TAFaultMIP, dvbnPlus1TAStuffingMode, dvbnPlus1TBRFPresent, dvbnPlus1TBInput1OK, dvbnPlus1TBInput2OK, 
				dvbnPlus1TBLocalMode, dvbnPlus1TBFault, dvbnPlus1TBWarning, dvbnPlus1TBInputPreselection, dvbnPlus1TBInputAutomatic, 
				dvbnPlus1TBActiveInput, dvbnPlus1TBSFNMode, dvbnPlus1TBRefFault, dvbnPlus1TBMute, dvbnPlus1TBFaultMIP, 
				dvbnPlus1TBStuffingMode, dvbnPlus1LocalModeEnable, dvbnPlus1ControlUnitFaultEnable, dvbnPlus1SwitchOverModeEnable, dvbnPlus1SwitchOverReadyEnable, 
				dvbnPlus1SwitchOverExecutedEnable, dvbnPlus1SwitchOverFaultEnable, dvbnPlus1ChannelSelectionEnable, dvbnPlus1MTInputPreselectionEnable, dvbnPlus1MTInputAutomaticEnable, 
				dvbnPlus1RTInputAutomaticEnable, dvbnPlus1RTOpModeEnable, dvbnPlus1TARFPresentEnable, dvbnPlus1TAInput1OKEnable, dvbnPlus1TAInput2OKEnable, 
				dvbnPlus1TALocalModeEnable, dvbnPlus1TAInputPreselectionEnable, dvbnPlus1TAInputAutomaticEnable, dvbnPlus1TAFaultEnable, dvbnPlus1TAWarningEnable, 
				dvbnPlus1TAActiveInputEnable, dvbnPlus1TASFNModeEnable, dvbnPlus1TARefFaultEnable, dvbnPlus1TAMuteEnable, dvbnPlus1TAFaultMIPEnable, 
				dvbnPlus1TAStuffingModeEnable, dvbnPlus1TBRFPresentEnable, dvbnPlus1TBInput1OKEnable, dvbnPlus1TBInput2OKEnable, dvbnPlus1TBLocalModeEnable, 
				dvbnPlus1TBFaultEnable, dvbnPlus1TBWarningEnable, dvbnPlus1TBInputPreselectionEnable, dvbnPlus1TBInputAutomaticEnable, dvbnPlus1TBActiveInputEnable, 
				dvbnPlus1TBSFNModeEnable, dvbnPlus1TBRefFaultEnable, dvbnPlus1TBMuteEnable, dvbnPlus1TBFaultMIPEnable, dvbnPlus1TBStuffingModeEnable, 
				dvbnPlus1LocalModePriority, dvbnPlus1ControlUnitFaultPriority, dvbnPlus1SwitchOverModePriority, dvbnPlus1SwitchOverReadyPriority, dvbnPlus1SwitchOverExecutedPriority, 
				dvbnPlus1SwitchOverFaultPriority, dvbnPlus1ChannelSelectionPriority, dvbnPlus1MTInputPreselectionPriority, dvbnPlus1MTInputAutomaticPriority, dvbnPlus1RTInputAutomaticPriority, 
				dvbnPlus1RTOpModePriority, dvbnPlus1TARFPresentPriority, dvbnPlus1TAInput1OKPriority, dvbnPlus1TAInput2OKPriority, dvbnPlus1TALocalModePriority, 
				dvbnPlus1TAInputPreselectionPriority, dvbnPlus1TAInputAutomaticPriority, dvbnPlus1TAFaultPriority, dvbnPlus1TAWarningPriority, dvbnPlus1TAActiveInputPriority, 
				dvbnPlus1TASFNModePriority, dvbnPlus1TARefFaultPriority, dvbnPlus1TAMutePriority, dvbnPlus1TAFaultMIPPriority, dvbnPlus1TAStuffingModePriority, 
				dvbnPlus1TBRFPresentPriority, dvbnPlus1TBInput1OKPriority, dvbnPlus1TBInput2OKPriority, dvbnPlus1TBLocalModePriority, dvbnPlus1TBFaultPriority, 
				dvbnPlus1TBWarningPriority, dvbnPlus1TBInputPreselectionPriority, dvbnPlus1TBActiveInputPriority, dvbnPlus1TBSFNModePriority, dvbnPlus1TBRefFaultPriority, 
				dvbnPlus1TBMutePriority, dvbnPlus1MTRFProgramPresentPriority, dvbnPlus1RTRFProgramPresentPriority, dvbnPlus1TBInputAutomaticPriority, dvbnPlus1MTRFProgramPresentEnable, 
				dvbnPlus1RTRFProgramPresentEnable, dvbnPlus1RTInputPreselectionPriority, dvbnPlus1MTOpModePriority, dvbnPlus1MTOpModeEnable, dvbnPlus1MTOpMode
				 }
			STATUS current
			DESCRIPTION 
				"Description.N+1 reserve: object group "
			::= { groupsnPlus1 1 }

		
		-- 1.3.6.1.4.1.19831.1.1.1.5.8.2
		eventGroupnPlus1 NOTIFICATION-GROUP
			NOTIFICATIONS { dvbnPlus1RedundancySwitchOverEvent, dvbnPlus1LocalModeEvent, dvbnPlus1ControlUnitFaultEvent, dvbnPlus1SwitchOverModeEvent, dvbnPlus1SwitchOverReadyEvent, 
				dvbnPlus1SwitchOverExecutedEvent, dvbnPlus1SwitchOverFaultEvent, dvbnPlus1ChannelSelectionEvent, dvbnPlus1MTInputPreselectionEvent, dvbnPlus1MTInputAutomaticEvent, 
				dvbnPlus1MTRFProgramPresentEvent, dvbnPlus1RTInputPreselectionEvent, dvbnPlus1RTInputAutomaticEvent, dvbnPlus1RTRFProgramPresentEvent, dvbnPlus1TARFPresentEvent, 
				dvbnPlus1TAInput1OKEvent, dvbnPlus1TAInput2OKEvent, dvbnPlus1TALocalModeEvent, dvbnPlus1TAInputPreselectionEvent, dvbnPlus1TAInputAutomaticEvent, 
				dvbnPlus1TAFaultEvent, dvbnPlus1TAWarningEvent, dvbnPlus1TAActiveInputEvent, dvbnPlus1TASFNModeEvent, dvbnPlus1TARefFaultEvent, 
				dvbnPlus1TAMuteEvent, dvbnPlus1TAFaultMIPEvent, dvbnPlus1TAStuffingModeEvent, dvbnPlus1TBRFPresentEvent, dvbnPlus1TBInput1OKEvent, 
				dvbnPlus1TBInput2OKEvent, dvbnPlus1TBLocalModeEvent, dvbnPlus1TBFaultEvent, dvbnPlus1TBWarningEvent, dvbnPlus1TBInputPreselectionEvent, 
				dvbnPlus1TBInputAutomaticEvent, dvbnPlus1TBActiveInputEvent, dvbnPlus1TBSFNModeEvent, dvbnPlus1TBRefFaultEvent, dvbnPlus1TBMuteEvent, 
				dvbnPlus1TBFaultMIPEvent, dvbnPlus1TBStuffingModeEvent, dvbnPlus1RTOpModeEvent, dvbnPlus1MTOpModeEvent }
			STATUS current
			DESCRIPTION 
				"Description.N+1 reserve: event group "
			::= { groupsnPlus1 2 }

		
		-- 1.3.6.1.4.1.19831.1.1.1.5.8.3
		objectGroupnPlus1obsolete OBJECT-GROUP
			OBJECTS { dvbnPlus1ResetFault, dvbnPlus1ResetFaultEnable, dvbnPlus1ResetFaultPriority, dvbnPlus1TransmitterBReset, dvbnPlus1TransmitterBMode, 
				dvbnPlus1TransmitterBResetEnable, dvbnPlus1TransmitterBModeEnable, dvbnPlus1TransmitterBResetPriority, dvbnPlus1TransmitterBModePriority }
			STATUS obsolete
			DESCRIPTION 
				"Description.Inactive objects"
			::= { groupsnPlus1 3 }

		
		-- 1.3.6.1.4.1.19831.1.1.1.5.8.4
		eventGroupnPlus1obsolete NOTIFICATION-GROUP
			NOTIFICATIONS { dvbnPlus1ResetFaultEvent, dvbnPlus1TransmitterBResetEvent, dvbnPlus1TransmitterBModeEvent }
			STATUS obsolete
			DESCRIPTION 
				"Description. Inactive events"
			::= { groupsnPlus1 4 }

		
		-- 1.3.6.1.4.1.19831.1.1.1.5.9
		compliancenPlus1 OBJECT IDENTIFIER ::= { dvbnPlus1 9 }

		
		-- 1.3.6.1.4.1.19831.1.1.1.5.9.1
		dvbnPlus1Compliance MODULE-COMPLIANCE
			STATUS current
			DESCRIPTION 
				"Description."
			MODULE -- this module
				MANDATORY-GROUPS { objectGroupnPlus1, eventGroupnPlus1 }
			::= { compliancenPlus1 1 }

		
	
	END

--
-- IRT-DVBT-NPLUS1-MIB.my
--
