--
-- IRT-DVBT-DUALDRIVE-MIB.my
-- MIB generated by MG-SOFT Visual MIB Builder Version 6.0  Build 88
-- Friday, May 04, 2007 at 17:31:47
--

	IRT-DVBT-DUALDRIVE-MIB DEFINITIONS ::= BEGIN
 
		IMPORTS
			eventTimeStamp, eventPriority, eventCounter, mibRelease			
				FROM IRT-COMMONVARBINDS-MIB			
			dvbT, Input1Input2, SelectManualAuto, SelectOnOff, PresentNotPresent, 
			FaultOK, WarningOK, LocalRemote, ReadyNotReady, ExecutedNotExecuted, 
			OkNotOk, MuteOk, SFNMFN			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DisplayString, TruthValue			
				FROM SNMPv2-TC;
	
	
		-- 1.3.6.1.4.1.19831.1.1.1.4
		dvbDualDrive MODULE-IDENTITY 
			LAST-UPDATED "200705041400Z"		-- May 04, 2007 at 14:00 GMT
			ORGANIZATION 
				"IRT for WORKING-GROUP-TC-MIB"
			CONTACT-INFO 
				"Contact-info:
				
				Andreas Metz
				
				Institut fuer Rundfunktechnik GmbH
				Broadcast Networks and Servers (SN)
				
				Floriansmuehlstr.60
				80939 Munich
				Germany
				
				Phone: +49 89 32399 325
				Fax: +49 89 32399 354 "
			DESCRIPTION 
				"Dual Drive
				
				branch definition
				
				1st level
				
				events               OBJECT IDENTIFIER ::= { dvbDualDrive 0 }
				dvbDDGeneral         OBJECT IDENTIFIER ::= { dvbDualDrive 1 }
				dvbDDExciterA        OBJECT IDENTIFIER ::= { dvbDualDrive 2 }
				dvbDDExciterB        OBJECT IDENTIFIER ::= { dvbDualDrive 3 }
				dvbDDEventEnable     OBJECT IDENTIFIER ::= { dvbDualDrive 4 }
				dvbDDEventPriority   OBJECT IDENTIFIER ::= { dvbDualDrive 5 }
				groups               OBJECT IDENTIFIER ::= { dvbDualDrive 6 }
				
				2nd level
				
				dvbDDEventEnableGeneral   OBJECT IDENTIFIER ::= { dvbDDEventEnable 1 }
				dvbDDEventEnableExciterA  OBJECT IDENTIFIER ::= { dvbDDEventEnable 2 }
				dvbDDEventEnableExciterB  OBJECT IDENTIFIER ::= { dvbDDEventEnable 3 }
				
				dvbDDEventPriorityGeneral   OBJECT IDENTIFIER ::= { dvbDDEventPriority 1 }
				dvbDDEventPriorityExciterA  OBJECT IDENTIFIER ::= { dvbDDEventPriority 2 }
				dvbDDEventPriorityExciterB  OBJECT IDENTIFIER ::= { dvbDDEventPriority 3 }
				
				end branch "
			REVISION "200705041400Z"		-- May 04, 2007 at 14:00 GMT
			DESCRIPTION 
				"change SFNMode, LocalMode (description only) and Module-COMPLIANCE"
			REVISION "200612201400Z"		-- December 20, 2006 at 14:00 GMT
			DESCRIPTION 
				"Corrections
				"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dvbT 4 }

		
	
	
--
-- Node definitions
--
	
-- dvb dual drive events
		-- 1.3.6.1.4.1.19831.1.1.1.4.0
		dvbEventsDD OBJECT IDENTIFIER ::= { dvbDualDrive 0 }

		
		-- 1.3.6.1.4.1.19831.1.1.1.4.0.1
		dvbDDInputPreselectionEvent NOTIFICATION-TYPE
			OBJECTS { sysDescr, sysName, sysLocation, eventTimeStamp, eventPriority, 
				eventCounter, dvbDDInputPreselection }
			STATUS current
			DESCRIPTION 
				"Description. dvbDDInputPreselection notification"
			::= { dvbEventsDD 1 }

		
		-- 1.3.6.1.4.1.19831.1.1.1.4.0.2
		dvbDDInputAutomaticEvent NOTIFICATION-TYPE
			OBJECTS { sysDescr, sysName, sysLocation, eventTimeStamp, eventPriority, 
				eventCounter, dvbDDInputAutomatic }
			STATUS current
			DESCRIPTION 
				"Description. dvbDDInputAutomatic notification"
			::= { dvbEventsDD 2 }

		
		-- 1.3.6.1.4.1.19831.1.1.1.4.0.3
		dvbDDPreselectionExciterEvent NOTIFICATION-TYPE
			OBJECTS { sysDescr, sysName, sysLocation, eventTimeStamp, eventPriority, 
				eventCounter, dvbDDPreselectionExciter }
			STATUS current
			DESCRIPTION 
				"Description. dvbDDPreselectionExciterEvent notification"
			::= { dvbEventsDD 3 }

		
		-- 1.3.6.1.4.1.19831.1.1.1.4.0.4
		dvbDDTransmitterOpModeEvent NOTIFICATION-TYPE
			OBJECTS { sysDescr, sysName, sysLocation, eventTimeStamp, eventPriority, 
				eventCounter, dvbDDTransmitterOpMode }
			STATUS current
			DESCRIPTION 
				"Description. dvbDDTransmitterOpMode notification"
			::= { dvbEventsDD 4 }

		
		-- 1.3.6.1.4.1.19831.1.1.1.4.0.5
		dvbDDReserveControlEvent NOTIFICATION-TYPE
			OBJECTS { sysDescr, sysName, sysLocation, eventTimeStamp, eventPriority, 
				eventCounter, dvbDDReserveControl }
			STATUS current
			DESCRIPTION 
				"Description. dvbDDReserveControl nitification"
			::= { dvbEventsDD 5 }

		
		-- 1.3.6.1.4.1.19831.1.1.1.4.0.6
		dvbDDRFPresentEvent NOTIFICATION-TYPE
			OBJECTS { sysDescr, sysName, sysLocation, eventTimeStamp, eventPriority, 
				eventCounter, dvbDDRFPresent }
			STATUS current
			DESCRIPTION 
				"Description. dvbDDRFPresent notification"
			::= { dvbEventsDD 6 }

		
		-- 1.3.6.1.4.1.19831.1.1.1.4.0.7
		dvbDDResetFaultEvent NOTIFICATION-TYPE
			OBJECTS { sysDescr, sysName, sysLocation, eventTimeStamp, eventPriority, 
				eventCounter, dvbDDResetFault }
			STATUS obsolete
			DESCRIPTION 
				"Notification is inactive!
				
				Description. dvbDDResetFault notification"
			::= { dvbEventsDD 7 }

		
		-- 1.3.6.1.4.1.19831.1.1.1.4.0.8
		dvbDDAmplifierFaultEvent NOTIFICATION-TYPE
			OBJECTS { sysDescr, sysName, sysLocation, eventTimeStamp, eventPriority, 
				eventCounter, dvbDDAmplifierFault }
			STATUS current
			DESCRIPTION 
				"Description. dvbDDAmplifierFault notification"
			::= { dvbEventsDD 8 }

		
		-- 1.3.6.1.4.1.19831.1.1.1.4.0.9
		dvbDDAmplifierWarningEvent NOTIFICATION-TYPE
			OBJECTS { sysDescr, sysName, sysLocation, eventTimeStamp, eventPriority, 
				eventCounter, dvbDDAmplifierWarning }
			STATUS current
			DESCRIPTION 
				"Description. dvbDDAmplifierWarning notification"
			::= { dvbEventsDD 9 }

		
		-- 1.3.6.1.4.1.19831.1.1.1.4.0.10
		dvbDDActiveExciterEvent NOTIFICATION-TYPE
			OBJECTS { sysDescr, sysName, sysLocation, eventTimeStamp, eventPriority, 
				eventCounter, dvbDDActiveExciter }
			STATUS current
			DESCRIPTION 
				"Description. dvbDDActiveExciter notification"
			::= { dvbEventsDD 10 }

		
		-- 1.3.6.1.4.1.19831.1.1.1.4.0.11
		dvbDDLocalModeEvent NOTIFICATION-TYPE
			OBJECTS { sysDescr, sysName, sysLocation, eventTimeStamp, eventPriority, 
				eventCounter, dvbDDLocalMode }
			STATUS current
			DESCRIPTION 
				"Description. dvbDDLocalMode notification"
			::= { dvbEventsDD 11 }

		
		-- 1.3.6.1.4.1.19831.1.1.1.4.0.12
		dvbDDControlUnitFaultEvent NOTIFICATION-TYPE
			OBJECTS { sysDescr, sysName, sysLocation, eventTimeStamp, eventPriority, 
				eventCounter, dvbDDControlUnitFault }
			STATUS current
			DESCRIPTION 
				"Description. dvbDDControlUnitFault notification"
			::= { dvbEventsDD 12 }

		
		-- 1.3.6.1.4.1.19831.1.1.1.4.0.13
		dvbDDSwitchOverModeEvent NOTIFICATION-TYPE
			OBJECTS { sysDescr, sysName, sysLocation, eventTimeStamp, eventPriority, 
				eventCounter, dvbDDSwitchOverMode }
			STATUS current
			DESCRIPTION 
				"Description. dvbDDSwitchOverMode notification"
			::= { dvbEventsDD 13 }

		
		-- 1.3.6.1.4.1.19831.1.1.1.4.0.14
		dvbDDSwitchOverReadyEvent NOTIFICATION-TYPE
			OBJECTS { sysDescr, sysName, sysLocation, eventTimeStamp, eventPriority, 
				eventCounter, dvbDDSwitchOverReady }
			STATUS current
			DESCRIPTION 
				"Description. dvbDDSwitchOverReady notification"
			::= { dvbEventsDD 14 }

		
		-- 1.3.6.1.4.1.19831.1.1.1.4.0.15
		dvbDDSwitchOverExecutedEvent NOTIFICATION-TYPE
			OBJECTS { sysDescr, sysName, sysLocation, eventTimeStamp, eventPriority, 
				eventCounter, dvbDDSwitchOverExecuted }
			STATUS current
			DESCRIPTION 
				"Description. dvbDDSwitchOverExecuted notification"
			::= { dvbEventsDD 15 }

		
		-- 1.3.6.1.4.1.19831.1.1.1.4.0.16
		dvbDDSwitchOverFaultEvent NOTIFICATION-TYPE
			OBJECTS { sysDescr, sysName, sysLocation, eventTimeStamp, eventPriority, 
				eventCounter, dvbDDSwitchOverFault }
			STATUS current
			DESCRIPTION 
				"Description. dvbDDSwitchOverFault notification"
			::= { dvbEventsDD 16 }

		
		-- 1.3.6.1.4.1.19831.1.1.1.4.0.17
		dvbDDExciterAInput1OKEvent NOTIFICATION-TYPE
			OBJECTS { sysDescr, sysName, sysLocation, eventTimeStamp, eventPriority, 
				eventCounter, dvbDDExciterAInput1OK }
			STATUS current
			DESCRIPTION 
				"Description. dvbDDExciterAInput1OK notification"
			::= { dvbEventsDD 17 }

		
		-- 1.3.6.1.4.1.19831.1.1.1.4.0.18
		dvbDDExciterAInput2OKEvent NOTIFICATION-TYPE
			OBJECTS { sysDescr, sysName, sysLocation, eventTimeStamp, eventPriority, 
				eventCounter, dvbDDExciterAInput2OK }
			STATUS current
			DESCRIPTION 
				"Description. dvbDDExciterAInput2OK notification"
			::= { dvbEventsDD 18 }

		
		-- 1.3.6.1.4.1.19831.1.1.1.4.0.19
		dvbDDExciterALocalModeEvent NOTIFICATION-TYPE
			OBJECTS { sysDescr, sysName, sysLocation, eventTimeStamp, eventPriority, 
				eventCounter, dvbDDExciterALocalMode }
			STATUS current
			DESCRIPTION 
				"Description. dvbDDExciterALocalMode notification"
			::= { dvbEventsDD 19 }

		
		-- 1.3.6.1.4.1.19831.1.1.1.4.0.20
		dvbDDExciterAFaultEvent NOTIFICATION-TYPE
			OBJECTS { sysDescr, sysName, sysLocation, eventTimeStamp, eventPriority, 
				eventCounter, dvbDDExciterAFault }
			STATUS current
			DESCRIPTION 
				"Description. dvbDDExciterAFault notification"
			::= { dvbEventsDD 20 }

		
		-- 1.3.6.1.4.1.19831.1.1.1.4.0.21
		dvbDDExciterAWarningEvent NOTIFICATION-TYPE
			OBJECTS { sysDescr, sysName, sysLocation, eventTimeStamp, eventPriority, 
				eventCounter, dvbDDExciterAWarning }
			STATUS current
			DESCRIPTION 
				"Description. dvbDDExciterAWarning notification"
			::= { dvbEventsDD 21 }

		
		-- 1.3.6.1.4.1.19831.1.1.1.4.0.22
		dvbDDExciterAActiveInputEvent NOTIFICATION-TYPE
			OBJECTS { sysDescr, sysName, sysLocation, eventTimeStamp, eventPriority, 
				eventCounter, dvbDDExciterAActiveInput }
			STATUS current
			DESCRIPTION 
				"Description. dvbDDExciterAActiveInput notification"
			::= { dvbEventsDD 22 }

		
		-- 1.3.6.1.4.1.19831.1.1.1.4.0.23
		dvbDDExciterASFNModeEvent NOTIFICATION-TYPE
			OBJECTS { sysDescr, sysName, sysLocation, eventTimeStamp, eventPriority, 
				eventCounter, dvbDDExciterASFNMode }
			STATUS current
			DESCRIPTION 
				"Description. dvbDDExciterASFNMode notification"
			::= { dvbEventsDD 23 }

		
		-- 1.3.6.1.4.1.19831.1.1.1.4.0.24
		dvbDDExciterARefFaultEvent NOTIFICATION-TYPE
			OBJECTS { sysDescr, sysName, sysLocation, eventTimeStamp, eventPriority, 
				eventCounter, dvbDDExciterARefFault }
			STATUS current
			DESCRIPTION 
				"Description. dvbDDExciterARefFault notification"
			::= { dvbEventsDD 24 }

		
		-- 1.3.6.1.4.1.19831.1.1.1.4.0.25
		dvbDDExciterAMuteEvent NOTIFICATION-TYPE
			OBJECTS { sysDescr, sysName, sysLocation, eventTimeStamp, eventPriority, 
				eventCounter, dvbDDExciterAMute }
			STATUS current
			DESCRIPTION 
				"Description. dvbDDExciterAMute notification"
			::= { dvbEventsDD 25 }

		
		-- 1.3.6.1.4.1.19831.1.1.1.4.0.26
		dvbDDExciterAFaultMIPEvent NOTIFICATION-TYPE
			OBJECTS { sysDescr, sysName, sysLocation, eventTimeStamp, eventPriority, 
				eventCounter, dvbDDExciterAFaultMIP }
			STATUS current
			DESCRIPTION 
				"Description. dvbDDExciterAFaultMIP notification"
			::= { dvbEventsDD 26 }

		
		-- 1.3.6.1.4.1.19831.1.1.1.4.0.27
		dvbDDExciterAStuffingModeEvent NOTIFICATION-TYPE
			OBJECTS { sysDescr, sysName, sysLocation, eventTimeStamp, eventPriority, 
				eventCounter, dvbDDExciterAStuffingMode }
			STATUS current
			DESCRIPTION 
				"Description. dvbDDExciterAStuffingMode notification"
			::= { dvbEventsDD 27 }

		
		-- 1.3.6.1.4.1.19831.1.1.1.4.0.28
		dvbDDExciterBInput1OKEvent NOTIFICATION-TYPE
			OBJECTS { sysDescr, sysName, sysLocation, eventTimeStamp, eventPriority, 
				eventCounter, dvbDDExciterBInput1OK }
			STATUS current
			DESCRIPTION 
				"Description. dvbDDExciterBInput1OK notification"
			::= { dvbEventsDD 28 }

		
		-- 1.3.6.1.4.1.19831.1.1.1.4.0.29
		dvbDDExciterBInput2OKEvent NOTIFICATION-TYPE
			OBJECTS { sysDescr, sysName, sysLocation, eventTimeStamp, eventPriority, 
				eventCounter, dvbDDExciterBInput2OK }
			STATUS current
			DESCRIPTION 
				"Description. dvbDDExciterBInput2OK notification"
			::= { dvbEventsDD 29 }

		
		-- 1.3.6.1.4.1.19831.1.1.1.4.0.30
		dvbDDExciterBLocalModeEvent NOTIFICATION-TYPE
			OBJECTS { sysDescr, sysName, sysLocation, eventTimeStamp, eventPriority, 
				eventCounter, dvbDDExciterBLocalMode }
			STATUS current
			DESCRIPTION 
				"Description. dvbDDExciterBLocalMode notification"
			::= { dvbEventsDD 30 }

		
		-- 1.3.6.1.4.1.19831.1.1.1.4.0.31
		dvbDDExciterBFaultEvent NOTIFICATION-TYPE
			OBJECTS { sysDescr, sysName, sysLocation, eventTimeStamp, eventPriority, 
				eventCounter, dvbDDExciterBFault }
			STATUS current
			DESCRIPTION 
				"Description. dvbDDExciterBFault notification"
			::= { dvbEventsDD 31 }

		
		-- 1.3.6.1.4.1.19831.1.1.1.4.0.32
		dvbDDExciterBWarningEvent NOTIFICATION-TYPE
			OBJECTS { sysDescr, sysName, sysLocation, eventTimeStamp, eventPriority, 
				eventCounter, dvbDDExciterBWarning }
			STATUS current
			DESCRIPTION 
				"Description. dvbDDExciterBWarning notification"
			::= { dvbEventsDD 32 }

		
		-- 1.3.6.1.4.1.19831.1.1.1.4.0.33
		dvbDDExciterBActiveInputEvent NOTIFICATION-TYPE
			OBJECTS { sysDescr, sysName, sysLocation, eventTimeStamp, eventPriority, 
				eventCounter, dvbDDExciterBActiveInput }
			STATUS current
			DESCRIPTION 
				"Description. dvbDDExciterBActiveInput notification"
			::= { dvbEventsDD 33 }

		
		-- 1.3.6.1.4.1.19831.1.1.1.4.0.34
		dvbDDExciterBSFNModeEvent NOTIFICATION-TYPE
			OBJECTS { sysDescr, sysName, sysLocation, eventTimeStamp, eventPriority, 
				eventCounter, dvbDDExciterBSFNMode }
			STATUS current
			DESCRIPTION 
				"Description. dvbDDExciterBSFNMode notification"
			::= { dvbEventsDD 34 }

		
		-- 1.3.6.1.4.1.19831.1.1.1.4.0.35
		dvbDDExciterBRefFaultEvent NOTIFICATION-TYPE
			OBJECTS { sysDescr, sysName, sysLocation, eventTimeStamp, eventPriority, 
				eventCounter, dvbDDExciterBRefFault }
			STATUS current
			DESCRIPTION 
				"Description. dvbDDExciterBRefFault notification"
			::= { dvbEventsDD 35 }

		
		-- 1.3.6.1.4.1.19831.1.1.1.4.0.36
		dvbDDExciterBMuteEvent NOTIFICATION-TYPE
			OBJECTS { sysDescr, sysName, sysLocation, eventTimeStamp, eventPriority, 
				eventCounter, dvbDDExciterBMute }
			STATUS current
			DESCRIPTION 
				"Description. dvbDDExciterBMute notification"
			::= { dvbEventsDD 36 }

		
		-- 1.3.6.1.4.1.19831.1.1.1.4.0.37
		dvbDDExciterBFaultMIPEvent NOTIFICATION-TYPE
			OBJECTS { sysDescr, sysName, sysLocation, eventTimeStamp, eventPriority, 
				eventCounter, dvbDDExciterBFaultMIP }
			STATUS current
			DESCRIPTION 
				"Description. dvbDDExciterBFaultMIP notification"
			::= { dvbEventsDD 37 }

		
		-- 1.3.6.1.4.1.19831.1.1.1.4.0.38
		dvbDDExciterBStuffingModeEvent NOTIFICATION-TYPE
			OBJECTS { sysDescr, sysName, sysLocation, eventTimeStamp, eventPriority, 
				eventCounter, dvbDDExciterBStuffingMode }
			STATUS current
			DESCRIPTION 
				"Description. dvbDDExciterBStuffingMode notification"
			::= { dvbEventsDD 38 }

		
-- dvb dual drive general
		-- 1.3.6.1.4.1.19831.1.1.1.4.1
		dvbDDGeneral OBJECT IDENTIFIER ::= { dvbDualDrive 1 }

		
		-- 1.3.6.1.4.1.19831.1.1.1.4.1.1
		dvbDDInputPreselection OBJECT-TYPE
			SYNTAX Input1Input2
			MAX-ACCESS read-write
			STATUS current
			DESCRIPTION
				"Dual drive. Preselection input 
				
				(0) undefined
				(1) Input 1
				(2) Input 2"
			::= { dvbDDGeneral 1 }

		
		-- 1.3.6.1.4.1.19831.1.1.1.4.1.2
		dvbDDInputAutomatic OBJECT-TYPE
			SYNTAX SelectManualAuto
			MAX-ACCESS read-write
			STATUS current
			DESCRIPTION
				"Dual drive. Input selection mode: manual or automatic
				
				(0) undefined
				(1) manual 
				(2) automatic"
			::= { dvbDDGeneral 2 }

		
		-- 1.3.6.1.4.1.19831.1.1.1.4.1.3
		dvbDDPreselectionExciter OBJECT-TYPE
			SYNTAX INTEGER
				{
				undefined(0),
				exciterA(1),
				exciterB(2)
				}
			MAX-ACCESS read-write
			STATUS current
			DESCRIPTION
				"Dual drive. Preselection of the exciter 
				
				
				"
			::= { dvbDDGeneral 3 }

		
		-- 1.3.6.1.4.1.19831.1.1.1.4.1.4
		dvbDDTransmitterOpMode OBJECT-TYPE
			SYNTAX SelectOnOff
			MAX-ACCESS read-write
			STATUS current
			DESCRIPTION
				"Dual drive. Operation mode of main exciter 
				
				(0) undefined
				(1) ON
				(2) OFF"
			::= { dvbDDGeneral 4 }

		
		-- 1.3.6.1.4.1.19831.1.1.1.4.1.5
		dvbDDReserveControl OBJECT-TYPE
			SYNTAX SelectOnOff
			MAX-ACCESS read-write
			STATUS current
			DESCRIPTION
				"Dual drive. Operation mode of reserve exciter
				
				(0) undefined
				(1) ON 
				(2) OFF "
			::= { dvbDDGeneral 5 }

		
		-- 1.3.6.1.4.1.19831.1.1.1.4.1.6
		dvbDDRFPresent OBJECT-TYPE
			SYNTAX PresentNotPresent
			MAX-ACCESS read-only
			STATUS current
			DESCRIPTION
				"Dual drive. Output power is present
				
				(0) undefined
				(1) present
				(2) not present"
			::= { dvbDDGeneral 6 }

		
		-- 1.3.6.1.4.1.19831.1.1.1.4.1.7
		dvbDDResetFault OBJECT-TYPE
			SYNTAX Unsigned32
			MAX-ACCESS read-write
			STATUS obsolete
			DESCRIPTION
				"Massage is inactive!
				
				Description.Trigger for reset the sum fault
				
				<1>
				1: reset sum fault"
			::= { dvbDDGeneral 7 }

		
		-- 1.3.6.1.4.1.19831.1.1.1.4.1.8
		dvbDDAmplifierFault OBJECT-TYPE
			SYNTAX FaultOK
			MAX-ACCESS read-only
			STATUS current
			DESCRIPTION
				"Dual drive. Fault state of amplifier 
				
				(0) undefined
				(1) fault
				(2) ok"
			::= { dvbDDGeneral 8 }

		
		-- 1.3.6.1.4.1.19831.1.1.1.4.1.9
		dvbDDAmplifierWarning OBJECT-TYPE
			SYNTAX WarningOK
			MAX-ACCESS read-only
			STATUS current
			DESCRIPTION
				"Dual drive. Warning state of amplifier 
				
				(0) undefined
				(1) warning
				(2) ok"
			::= { dvbDDGeneral 9 }

		
		-- 1.3.6.1.4.1.19831.1.1.1.4.1.10
		dvbDDActiveExciter OBJECT-TYPE
			SYNTAX INTEGER
				{
				undefined(0),
				exciterA(1),
				exciterB(2)
				}
			MAX-ACCESS read-only
			STATUS current
			DESCRIPTION
				"Dual drive. Active exciter 
				
				
				"
			::= { dvbDDGeneral 10 }

		
		-- 1.3.6.1.4.1.19831.1.1.1.4.1.11
		dvbDDLocalMode OBJECT-TYPE
			SYNTAX LocalRemote
			MAX-ACCESS read-only
			STATUS current
			DESCRIPTION
				"Dual drive. Local mode
				
				(0) undefined
				(1) local
				(2) remote"
			::= { dvbDDGeneral 11 }

		
		-- 1.3.6.1.4.1.19831.1.1.1.4.1.12
		dvbDDControlUnitFault OBJECT-TYPE
			SYNTAX FaultOK
			MAX-ACCESS read-only
			STATUS current
			DESCRIPTION
				"Dual drive. State of the control unit
				
				(0) undefined
				(1) fault
				(2) ok"
			::= { dvbDDGeneral 12 }

		
		-- 1.3.6.1.4.1.19831.1.1.1.4.1.13
		dvbDDSwitchOverMode OBJECT-TYPE
			SYNTAX SelectManualAuto
			MAX-ACCESS read-write
			STATUS current
			DESCRIPTION
				"Dual drive. Switch over mode: manual or automatic
				
				(0) undefined
				(1) manual 
				(2) automatic"
			::= { dvbDDGeneral 13 }

		
		-- 1.3.6.1.4.1.19831.1.1.1.4.1.14
		dvbDDSwitchOverReady OBJECT-TYPE
			SYNTAX ReadyNotReady
			MAX-ACCESS read-only
			STATUS current
			DESCRIPTION
				"Dual drive. State of the dual drive switch over unit
				
				(0) undefined
				(1) ready
				(2) not ready"
			::= { dvbDDGeneral 14 }

		
		-- 1.3.6.1.4.1.19831.1.1.1.4.1.15
		dvbDDSwitchOverExecuted OBJECT-TYPE
			SYNTAX ExecutedNotExecuted
			MAX-ACCESS read-only
			STATUS current
			DESCRIPTION
				"Dual drive. Showsif the reserve switch over unit it has executed
				
				(0) undefined
				(1) excecuted
				(2) not excecuted"
			::= { dvbDDGeneral 15 }

		
		-- 1.3.6.1.4.1.19831.1.1.1.4.1.16
		dvbDDSwitchOverFault OBJECT-TYPE
			SYNTAX FaultOK
			MAX-ACCESS read-only
			STATUS current
			DESCRIPTION
				"Dual drive. fault state of the switsch over unit
				
				(0) undefined
				(1) faulty
				(2) ok"
			::= { dvbDDGeneral 16 }

		
-- dvb dual drive exciter A
		-- 1.3.6.1.4.1.19831.1.1.1.4.2
		dvbDDExciterA OBJECT IDENTIFIER ::= { dvbDualDrive 2 }

		
--   
		-- 1.3.6.1.4.1.19831.1.1.1.4.2.1
		dvbDDExciterAInput1OK OBJECT-TYPE
			SYNTAX OkNotOk
			MAX-ACCESS read-only
			STATUS current
			DESCRIPTION
				"Dual drive. Describes if the input signal at the input 1 of exciter A is ok
				
				(0) undefined
				(1) signal ok
				(2) signal is not ok"
			::= { dvbDDExciterA 1 }

		
--    
		-- 1.3.6.1.4.1.19831.1.1.1.4.2.2
		dvbDDExciterAInput2OK OBJECT-TYPE
			SYNTAX OkNotOk
			MAX-ACCESS read-only
			STATUS current
			DESCRIPTION
				"Dual drive. Describes if the input signal at the input 2 of exciter A is ok
				
				(0) undefined
				(1) signal ok
				(2) signal is not ok"
			::= { dvbDDExciterA 2 }

		
--   
		-- 1.3.6.1.4.1.19831.1.1.1.4.2.3
		dvbDDExciterALocalMode OBJECT-TYPE
			SYNTAX LocalRemote
			MAX-ACCESS read-only
			STATUS current
			DESCRIPTION
				"Dual drive. Local mode of exciter A
				
				(0) undefined
				(1) local
				(2) remote"
			::= { dvbDDExciterA 3 }

		
--   
		-- 1.3.6.1.4.1.19831.1.1.1.4.2.4
		dvbDDExciterAFault OBJECT-TYPE
			SYNTAX FaultOK
			MAX-ACCESS read-only
			STATUS current
			DESCRIPTION
				"Dual drive. Fault state of exciter A
				
				(0) undefined
				(1) fault
				(2) ok"
			::= { dvbDDExciterA 4 }

		
--  
		-- 1.3.6.1.4.1.19831.1.1.1.4.2.5
		dvbDDExciterAWarning OBJECT-TYPE
			SYNTAX WarningOK
			MAX-ACCESS read-only
			STATUS current
			DESCRIPTION
				"Dual drive.Warning state of exciter A 
				
				(0) undefined
				(1) warning
				(2) ok"
			::= { dvbDDExciterA 5 }

		
--    
		-- 1.3.6.1.4.1.19831.1.1.1.4.2.6
		dvbDDExciterAActiveInput OBJECT-TYPE
			SYNTAX INTEGER
				{
				undefined(0),
				input1(1),
				input2(2),
				seamless(3),
				hmHierarchicalModulation(4)
				}
			MAX-ACCESS read-only
			STATUS current
			DESCRIPTION
				"Dual drive. Active input of the exciter A 
				
				"
			::= { dvbDDExciterA 6 }

		
--    
		-- 1.3.6.1.4.1.19831.1.1.1.4.2.7
		dvbDDExciterASFNMode OBJECT-TYPE
			SYNTAX SFNMFN
			MAX-ACCESS read-only
			STATUS current
			DESCRIPTION
				"Dual drive. SFN mode of exciter A
				
				(0) undefined
				(1) SFN
				(2) MFN
				
				"
			::= { dvbDDExciterA 7 }

		
--    
		-- 1.3.6.1.4.1.19831.1.1.1.4.2.8
		dvbDDExciterARefFault OBJECT-TYPE
			SYNTAX FaultOK
			MAX-ACCESS read-only
			STATUS current
			DESCRIPTION
				"Dual drive. Fault state of the GPS input or the reference frequency of exciter A
				
				(0) undefined
				(1) fault
				(2) ok"
			::= { dvbDDExciterA 8 }

		
--  
		-- 1.3.6.1.4.1.19831.1.1.1.4.2.9
		dvbDDExciterAMute OBJECT-TYPE
			SYNTAX MuteOk
			MAX-ACCESS read-only
			STATUS current
			DESCRIPTION
				"Dual drive. Mute state of exciter A
				
				(0) undefined
				(1) mute
				(2) ok"
			::= { dvbDDExciterA 9 }

		
--    
		-- 1.3.6.1.4.1.19831.1.1.1.4.2.10
		dvbDDExciterAFaultMIP OBJECT-TYPE
			SYNTAX FaultOK
			MAX-ACCESS read-only
			STATUS current
			DESCRIPTION
				"Dual drive. MIP fault state of exciter A
				
				(0) undefined
				(1) fault
				(2) ok"
			::= { dvbDDExciterA 10 }

		
--  
		-- 1.3.6.1.4.1.19831.1.1.1.4.2.11
		dvbDDExciterAStuffingMode OBJECT-TYPE
			SYNTAX SelectOnOff
			MAX-ACCESS read-only
			STATUS current
			DESCRIPTION
				"Dual drive. Stuffing state of exciter A
				
				(0) undefined
				(1) ON 
				(2) OFF "
			::= { dvbDDExciterA 11 }

		
-- dvb dual drive exciter B
		-- 1.3.6.1.4.1.19831.1.1.1.4.3
		dvbDDExciterB OBJECT IDENTIFIER ::= { dvbDualDrive 3 }

		
--  
		-- 1.3.6.1.4.1.19831.1.1.1.4.3.1
		dvbDDExciterBInput1OK OBJECT-TYPE
			SYNTAX OkNotOk
			MAX-ACCESS read-only
			STATUS current
			DESCRIPTION
				"Dual drive. Describes if the input signal at the input 1 of exciter B is ok
				
				(0) undefined
				(1) signal ok
				(2) signal is not ok"
			::= { dvbDDExciterB 1 }

		
--   
		-- 1.3.6.1.4.1.19831.1.1.1.4.3.2
		dvbDDExciterBInput2OK OBJECT-TYPE
			SYNTAX OkNotOk
			MAX-ACCESS read-only
			STATUS current
			DESCRIPTION
				"Dual drive. Describes if the input signal at the input 2 of exciter B is ok
				
				(0) undefined
				(1) signal ok
				(2) signal is not ok "
			::= { dvbDDExciterB 2 }

		
--  
		-- 1.3.6.1.4.1.19831.1.1.1.4.3.3
		dvbDDExciterBLocalMode OBJECT-TYPE
			SYNTAX LocalRemote
			MAX-ACCESS read-only
			STATUS current
			DESCRIPTION
				"Dual drive. Local mode of exciter B
				
				(0) undefined
				(1) local
				(2) remote"
			::= { dvbDDExciterB 3 }

		
--   
		-- 1.3.6.1.4.1.19831.1.1.1.4.3.4
		dvbDDExciterBFault OBJECT-TYPE
			SYNTAX FaultOK
			MAX-ACCESS read-only
			STATUS current
			DESCRIPTION
				"Dual drive. Fault state of exciter B
				
				(0) undefined
				(1) fault
				(2) ok"
			::= { dvbDDExciterB 4 }

		
--   
		-- 1.3.6.1.4.1.19831.1.1.1.4.3.5
		dvbDDExciterBWarning OBJECT-TYPE
			SYNTAX WarningOK
			MAX-ACCESS read-only
			STATUS current
			DESCRIPTION
				"Dual drive. Warning state of exciter B 
				
				(0) undefined
				(1) warning
				(2) ok"
			::= { dvbDDExciterB 5 }

		
--  
		-- 1.3.6.1.4.1.19831.1.1.1.4.3.6
		dvbDDExciterBActiveInput OBJECT-TYPE
			SYNTAX INTEGER
				{
				undefined(0),
				input1(1),
				input2(2),
				seamless(3),
				hmHierarchicalModulation(4)
				}
			MAX-ACCESS read-only
			STATUS current
			DESCRIPTION
				"Dual drive. Active input of the exciter B 
				
				"
			::= { dvbDDExciterB 6 }

		
--    
		-- 1.3.6.1.4.1.19831.1.1.1.4.3.7
		dvbDDExciterBSFNMode OBJECT-TYPE
			SYNTAX SFNMFN
			MAX-ACCESS read-only
			STATUS current
			DESCRIPTION
				"Dual drive. SFN mode of exciter B
				
				(0) undefined
				(1) SFN
				(2) MFN"
			::= { dvbDDExciterB 7 }

		
--    
		-- 1.3.6.1.4.1.19831.1.1.1.4.3.8
		dvbDDExciterBRefFault OBJECT-TYPE
			SYNTAX FaultOK
			MAX-ACCESS read-only
			STATUS current
			DESCRIPTION
				"Dual drive. Fault state of the GPS input or the reference frequency of exciter B
				
				(0) undefined
				(1) fault
				(2) ok"
			::= { dvbDDExciterB 8 }

		
--   
		-- 1.3.6.1.4.1.19831.1.1.1.4.3.9
		dvbDDExciterBMute OBJECT-TYPE
			SYNTAX MuteOk
			MAX-ACCESS read-only
			STATUS current
			DESCRIPTION
				"Dual drive. Mute state of exciter B
				
				(0) undefined
				(1) mute
				(2) ok"
			::= { dvbDDExciterB 9 }

		
--   
		-- 1.3.6.1.4.1.19831.1.1.1.4.3.10
		dvbDDExciterBFaultMIP OBJECT-TYPE
			SYNTAX FaultOK
			MAX-ACCESS read-only
			STATUS current
			DESCRIPTION
				"Dual drive. MIP fault state of exciter B
				
				(0) undefined
				(1) fault
				(2) ok"
			::= { dvbDDExciterB 10 }

		
--    
		-- 1.3.6.1.4.1.19831.1.1.1.4.3.11
		dvbDDExciterBStuffingMode OBJECT-TYPE
			SYNTAX SelectOnOff
			MAX-ACCESS read-only
			STATUS current
			DESCRIPTION
				"Dual drive. Stuffing state of exciter B
				
				(0) undefined
				(1) ON 
				(2) OFF "
			::= { dvbDDExciterB 11 }

		
-- dvb dual drive: switch for Event
		-- 1.3.6.1.4.1.19831.1.1.1.4.4
		dvbDDEventEnable OBJECT IDENTIFIER ::= { dvbDualDrive 4 }

		
-- dvb dual drive general: switch for Event
		-- 1.3.6.1.4.1.19831.1.1.1.4.4.1
		dvbDDEventEnableGeneral OBJECT IDENTIFIER ::= { dvbDDEventEnable 1 }

		
		-- 1.3.6.1.4.1.19831.1.1.1.4.4.1.1
		dvbDDInputPreselectionEnable OBJECT-TYPE
			SYNTAX TruthValue
			MAX-ACCESS read-write
			STATUS current
			DESCRIPTION
				"Description. Enable/Disable switch for dvbDDInputPreselection event"
			::= { dvbDDEventEnableGeneral 1 }

		
		-- 1.3.6.1.4.1.19831.1.1.1.4.4.1.2
		dvbDDInputAutomaticEnable OBJECT-TYPE
			SYNTAX TruthValue
			MAX-ACCESS read-write
			STATUS current
			DESCRIPTION
				"Description. Enable/Disable switch for dvbDDInputAutomatic event"
			::= { dvbDDEventEnableGeneral 2 }

		
		-- 1.3.6.1.4.1.19831.1.1.1.4.4.1.3
		dvbDDPreselectionExciterEnable OBJECT-TYPE
			SYNTAX TruthValue
			MAX-ACCESS read-write
			STATUS current
			DESCRIPTION
				"Description. Enable/Disable switch for dvbDDPreselectionExciter event"
			::= { dvbDDEventEnableGeneral 3 }

		
		-- 1.3.6.1.4.1.19831.1.1.1.4.4.1.4
		dvbDDTransmitterOpModeEnable OBJECT-TYPE
			SYNTAX TruthValue
			MAX-ACCESS read-write
			STATUS current
			DESCRIPTION
				"Description. Enable/Disable switch for dvbDDTransmitterOpMode event"
			::= { dvbDDEventEnableGeneral 4 }

		
		-- 1.3.6.1.4.1.19831.1.1.1.4.4.1.5
		dvbDDReserveControlEnable OBJECT-TYPE
			SYNTAX TruthValue
			MAX-ACCESS read-write
			STATUS current
			DESCRIPTION
				"Description. Enable/Disable switch for dvbDDIReserveControl event"
			::= { dvbDDEventEnableGeneral 5 }

		
		-- 1.3.6.1.4.1.19831.1.1.1.4.4.1.6
		dvbDDRFPresentEnable OBJECT-TYPE
			SYNTAX TruthValue
			MAX-ACCESS read-write
			STATUS current
			DESCRIPTION
				"Description. Enable/Disable switch for dvbDDRFPresent event
				"
			::= { dvbDDEventEnableGeneral 6 }

		
		-- 1.3.6.1.4.1.19831.1.1.1.4.4.1.7
		dvbDDResetFaultEnable OBJECT-TYPE
			SYNTAX TruthValue
			MAX-ACCESS read-write
			STATUS obsolete
			DESCRIPTION
				"Massage ist inactive!
				
				
				Description. Enable/Disable switch for dvbDDResetFault event
				"
			::= { dvbDDEventEnableGeneral 7 }

		
		-- 1.3.6.1.4.1.19831.1.1.1.4.4.1.8
		dvbDDAmplifierFaultEnable OBJECT-TYPE
			SYNTAX TruthValue
			MAX-ACCESS read-write
			STATUS current
			DESCRIPTION
				"Description. Enable/Disable switch for dvbDDAmplifierFault event"
			::= { dvbDDEventEnableGeneral 8 }

		
		-- 1.3.6.1.4.1.19831.1.1.1.4.4.1.9
		dvbDDAmplifierWarningEnable OBJECT-TYPE
			SYNTAX TruthValue
			MAX-ACCESS read-write
			STATUS current
			DESCRIPTION
				"Description. Enable/Disable switch for dvbDDAmplifierWarning event"
			::= { dvbDDEventEnableGeneral 9 }

		
		-- 1.3.6.1.4.1.19831.1.1.1.4.4.1.10
		dvbDDActiveExciterEnable OBJECT-TYPE
			SYNTAX TruthValue
			MAX-ACCESS read-write
			STATUS current
			DESCRIPTION
				"Description. Enable/Disable switch for dvbDDActiveExciter event
				"
			::= { dvbDDEventEnableGeneral 10 }

		
		-- 1.3.6.1.4.1.19831.1.1.1.4.4.1.11
		dvbDDLocalModeEnable OBJECT-TYPE
			SYNTAX TruthValue
			MAX-ACCESS read-write
			STATUS current
			DESCRIPTION
				"Description. Enable/Disable switch for dvbDDLocalMode event"
			::= { dvbDDEventEnableGeneral 11 }

		
		-- 1.3.6.1.4.1.19831.1.1.1.4.4.1.12
		dvbDDControlUnitFaultEnable OBJECT-TYPE
			SYNTAX TruthValue
			MAX-ACCESS read-write
			STATUS current
			DESCRIPTION
				"Description. Enable/Disable switch for dvbDDControlUnitFault event"
			::= { dvbDDEventEnableGeneral 12 }

		
		-- 1.3.6.1.4.1.19831.1.1.1.4.4.1.13
		dvbDDSwitchOverModeEnable OBJECT-TYPE
			SYNTAX TruthValue
			MAX-ACCESS read-write
			STATUS current
			DESCRIPTION
				"Description. Enable/Disable switch for dvbDDSwitchOverMode event"
			::= { dvbDDEventEnableGeneral 13 }

		
		-- 1.3.6.1.4.1.19831.1.1.1.4.4.1.14
		dvbDDSwitchOverReadyEnable OBJECT-TYPE
			SYNTAX TruthValue
			MAX-ACCESS read-write
			STATUS current
			DESCRIPTION
				"Description. Enable/Disable switch for dvbDDSwitchOverReady event"
			::= { dvbDDEventEnableGeneral 14 }

		
		-- 1.3.6.1.4.1.19831.1.1.1.4.4.1.15
		dvbDDSwitchOverExecutedEnable OBJECT-TYPE
			SYNTAX TruthValue
			MAX-ACCESS read-write
			STATUS current
			DESCRIPTION
				"Description. Enable/Disable switch for dvbDDSwitchOverExecuted event"
			::= { dvbDDEventEnableGeneral 15 }

		
		-- 1.3.6.1.4.1.19831.1.1.1.4.4.1.16
		dvbDDSwitchOverFaultEnable OBJECT-TYPE
			SYNTAX TruthValue
			MAX-ACCESS read-write
			STATUS current
			DESCRIPTION
				"Description. Enable/Disable switch for dvbDDSwitchOverFault event"
			::= { dvbDDEventEnableGeneral 16 }

		
-- dvb dual drive exciter A: switch for Event
		-- 1.3.6.1.4.1.19831.1.1.1.4.4.2
		dvbDDEventEnableExciterA OBJECT IDENTIFIER ::= { dvbDDEventEnable 2 }

		
--   
		-- 1.3.6.1.4.1.19831.1.1.1.4.4.2.1
		dvbDDExciterAInput1OKEnable OBJECT-TYPE
			SYNTAX TruthValue
			MAX-ACCESS read-write
			STATUS current
			DESCRIPTION
				"Description. Enable/Disable switch for dvbDDExciterAInput1OK event"
			::= { dvbDDEventEnableExciterA 1 }

		
--    
		-- 1.3.6.1.4.1.19831.1.1.1.4.4.2.2
		dvbDDExciterAInput2OKEnable OBJECT-TYPE
			SYNTAX TruthValue
			MAX-ACCESS read-write
			STATUS current
			DESCRIPTION
				"Description. Enable/Disable switch for dvbDDExciterAInput2OK event"
			::= { dvbDDEventEnableExciterA 2 }

		
--   
		-- 1.3.6.1.4.1.19831.1.1.1.4.4.2.3
		dvbDDExciterALocalModeEnable OBJECT-TYPE
			SYNTAX TruthValue
			MAX-ACCESS read-write
			STATUS current
			DESCRIPTION
				"Description. Enable/Disable switch for dvbDDExciterALocalMode event"
			::= { dvbDDEventEnableExciterA 3 }

		
--   
		-- 1.3.6.1.4.1.19831.1.1.1.4.4.2.4
		dvbDDExciterAFaultEnable OBJECT-TYPE
			SYNTAX TruthValue
			MAX-ACCESS read-write
			STATUS current
			DESCRIPTION
				"Description. Enable/Disable switch for dvbDDExciterAFault  event"
			::= { dvbDDEventEnableExciterA 4 }

		
--  
		-- 1.3.6.1.4.1.19831.1.1.1.4.4.2.5
		dvbDDExciterAWarningEnable OBJECT-TYPE
			SYNTAX TruthValue
			MAX-ACCESS read-write
			STATUS current
			DESCRIPTION
				"Description. Enable/Disable switch for dvbDDExciterAWarning event"
			::= { dvbDDEventEnableExciterA 5 }

		
--    
		-- 1.3.6.1.4.1.19831.1.1.1.4.4.2.6
		dvbDDExciterAActiveInputEnable OBJECT-TYPE
			SYNTAX TruthValue
			MAX-ACCESS read-write
			STATUS current
			DESCRIPTION
				"Description. Enable/Disable switch for dvbDDExciterAActiveInput event"
			::= { dvbDDEventEnableExciterA 6 }

		
--    
		-- 1.3.6.1.4.1.19831.1.1.1.4.4.2.7
		dvbDDExciterASFNModeEnable OBJECT-TYPE
			SYNTAX TruthValue
			MAX-ACCESS read-write
			STATUS current
			DESCRIPTION
				"Description. Enable/Disable switch for dvbDDExciterASFNMode event"
			::= { dvbDDEventEnableExciterA 7 }

		
--    
		-- 1.3.6.1.4.1.19831.1.1.1.4.4.2.8
		dvbDDExciterARefFaultEnable OBJECT-TYPE
			SYNTAX TruthValue
			MAX-ACCESS read-write
			STATUS current
			DESCRIPTION
				"Description. Enable/Disable switch for dvbDDExciterARefFault event"
			::= { dvbDDEventEnableExciterA 8 }

		
--  
		-- 1.3.6.1.4.1.19831.1.1.1.4.4.2.9
		dvbDDExciterAMuteEnable OBJECT-TYPE
			SYNTAX TruthValue
			MAX-ACCESS read-write
			STATUS current
			DESCRIPTION
				"Description. Enable/Disable switch for dvbDDExciterAMute event"
			::= { dvbDDEventEnableExciterA 9 }

		
--    
		-- 1.3.6.1.4.1.19831.1.1.1.4.4.2.10
		dvbDDExciterAFaultMIPEnable OBJECT-TYPE
			SYNTAX TruthValue
			MAX-ACCESS read-write
			STATUS current
			DESCRIPTION
				"Description. Enable/Disable switch for dvbDDExciterAFaultMIP event"
			::= { dvbDDEventEnableExciterA 10 }

		
--  
		-- 1.3.6.1.4.1.19831.1.1.1.4.4.2.11
		dvbDDExciterAStuffingModeEnable OBJECT-TYPE
			SYNTAX TruthValue
			MAX-ACCESS read-write
			STATUS current
			DESCRIPTION
				"Description. Enable/Disable switch for dvbDDExciterAStuffingMode event"
			::= { dvbDDEventEnableExciterA 11 }

		
-- dvb dual drive exciter B: switch for Event
		-- 1.3.6.1.4.1.19831.1.1.1.4.4.3
		dvbDDEventEnableExciterB OBJECT IDENTIFIER ::= { dvbDDEventEnable 3 }

		
--  
		-- 1.3.6.1.4.1.19831.1.1.1.4.4.3.1
		dvbDDExciterBInput1OKEnable OBJECT-TYPE
			SYNTAX TruthValue
			MAX-ACCESS read-write
			STATUS current
			DESCRIPTION
				"Description. Enable/Disable switch for dvbDDExciterBInput1OK event"
			::= { dvbDDEventEnableExciterB 1 }

		
--   
		-- 1.3.6.1.4.1.19831.1.1.1.4.4.3.2
		dvbDDExciterBInput2OKEnable OBJECT-TYPE
			SYNTAX TruthValue
			MAX-ACCESS read-write
			STATUS current
			DESCRIPTION
				"Description. Enable/Disable switch for dvbDDExciterBInput2OK event"
			::= { dvbDDEventEnableExciterB 2 }

		
--  
		-- 1.3.6.1.4.1.19831.1.1.1.4.4.3.3
		dvbDDExciterBLocalModeEnable OBJECT-TYPE
			SYNTAX TruthValue
			MAX-ACCESS read-write
			STATUS current
			DESCRIPTION
				"Description. Enable/Disable switch for dvbDDExciterBLocalMode event"
			::= { dvbDDEventEnableExciterB 3 }

		
--   
		-- 1.3.6.1.4.1.19831.1.1.1.4.4.3.4
		dvbDDExciterBFaultEnable OBJECT-TYPE
			SYNTAX TruthValue
			MAX-ACCESS read-write
			STATUS current
			DESCRIPTION
				"Description. Enable/Disable switch for dvbDDExciterBFault event"
			::= { dvbDDEventEnableExciterB 4 }

		
--   
		-- 1.3.6.1.4.1.19831.1.1.1.4.4.3.5
		dvbDDExciterBWarningEnable OBJECT-TYPE
			SYNTAX TruthValue
			MAX-ACCESS read-write
			STATUS current
			DESCRIPTION
				"Description. Enable/Disable switch for dvbDDExciterBWarning event"
			::= { dvbDDEventEnableExciterB 5 }

		
--  
		-- 1.3.6.1.4.1.19831.1.1.1.4.4.3.6
		dvbDDExciterBActiveInputEnable OBJECT-TYPE
			SYNTAX TruthValue
			MAX-ACCESS read-write
			STATUS current
			DESCRIPTION
				"Description. Enable/Disable switch for dvbDDExciterBActiveInput event"
			::= { dvbDDEventEnableExciterB 6 }

		
--    
		-- 1.3.6.1.4.1.19831.1.1.1.4.4.3.7
		dvbDDExciterBSFNModeEnable OBJECT-TYPE
			SYNTAX TruthValue
			MAX-ACCESS read-write
			STATUS current
			DESCRIPTION
				"Description. Enable/Disable switch for dvbDDExciterBSFNMode event"
			::= { dvbDDEventEnableExciterB 7 }

		
--    
		-- 1.3.6.1.4.1.19831.1.1.1.4.4.3.8
		dvbDDExciterBRefFaultEnable OBJECT-TYPE
			SYNTAX TruthValue
			MAX-ACCESS read-write
			STATUS current
			DESCRIPTION
				"Description. Enable/Disable switch for dvbDDExciterBRefFault event"
			::= { dvbDDEventEnableExciterB 8 }

		
--   
		-- 1.3.6.1.4.1.19831.1.1.1.4.4.3.9
		dvbDDExciterBMuteEnable OBJECT-TYPE
			SYNTAX TruthValue
			MAX-ACCESS read-write
			STATUS current
			DESCRIPTION
				"Description. Enable/Disable switch for dvbDDExciterBMute event"
			::= { dvbDDEventEnableExciterB 9 }

		
--   
		-- 1.3.6.1.4.1.19831.1.1.1.4.4.3.10
		dvbDDExciterBFaultMIPEnable OBJECT-TYPE
			SYNTAX TruthValue
			MAX-ACCESS read-write
			STATUS current
			DESCRIPTION
				"Description. Enable/Disable switch for dvbDDExciterBFaultMIP event"
			::= { dvbDDEventEnableExciterB 10 }

		
--    
		-- 1.3.6.1.4.1.19831.1.1.1.4.4.3.11
		dvbDDExciterBStuffingModeEnable OBJECT-TYPE
			SYNTAX TruthValue
			MAX-ACCESS read-write
			STATUS current
			DESCRIPTION
				"Description. Enable/Disable switch for dvbDDExciterBStuffingMode event"
			::= { dvbDDEventEnableExciterB 11 }

		
-- dvb dual drive event priority
		-- 1.3.6.1.4.1.19831.1.1.1.4.5
		dvbDDEventPriority OBJECT IDENTIFIER ::= { dvbDualDrive 5 }

		
-- dvb dual drive: general event priority
		-- 1.3.6.1.4.1.19831.1.1.1.4.5.1
		dvbDDEventPriorityGeneral OBJECT IDENTIFIER ::= { dvbDDEventPriority 1 }

		
		-- 1.3.6.1.4.1.19831.1.1.1.4.5.1.1
		dvbDDInputPreselectionPriority OBJECT-TYPE
			SYNTAX Unsigned32
			MAX-ACCESS read-write
			STATUS current
			DESCRIPTION
				"Description. Priority for dvbDDInputPreselection event"
			::= { dvbDDEventPriorityGeneral 1 }

		
		-- 1.3.6.1.4.1.19831.1.1.1.4.5.1.2
		dvbDDInputAutomaticPriority OBJECT-TYPE
			SYNTAX Unsigned32
			MAX-ACCESS read-write
			STATUS current
			DESCRIPTION
				"Description. Priority for dvbDDInputAutomatic event"
			::= { dvbDDEventPriorityGeneral 2 }

		
		-- 1.3.6.1.4.1.19831.1.1.1.4.5.1.3
		dvbDDPreselectionExciterPriority OBJECT-TYPE
			SYNTAX Unsigned32
			MAX-ACCESS read-write
			STATUS current
			DESCRIPTION
				"Description. Priority for dvbDDInputExciter event"
			::= { dvbDDEventPriorityGeneral 3 }

		
		-- 1.3.6.1.4.1.19831.1.1.1.4.5.1.4
		dvbDDTransmitterOpModePriority OBJECT-TYPE
			SYNTAX Unsigned32
			MAX-ACCESS read-write
			STATUS current
			DESCRIPTION
				"Description. Priority for dvbDDTransmitterOpMode event"
			::= { dvbDDEventPriorityGeneral 4 }

		
		-- 1.3.6.1.4.1.19831.1.1.1.4.5.1.5
		dvbDDReserveControlPriority OBJECT-TYPE
			SYNTAX Unsigned32
			MAX-ACCESS read-write
			STATUS current
			DESCRIPTION
				"Description. Priority for dvbDDReserveControl event"
			::= { dvbDDEventPriorityGeneral 5 }

		
		-- 1.3.6.1.4.1.19831.1.1.1.4.5.1.6
		dvbDDRFPresentPriority OBJECT-TYPE
			SYNTAX Unsigned32
			MAX-ACCESS read-write
			STATUS current
			DESCRIPTION
				"Description. Priority for dvbDDRFPresent event"
			::= { dvbDDEventPriorityGeneral 6 }

		
		-- 1.3.6.1.4.1.19831.1.1.1.4.5.1.7
		dvbDDResetFaultPriority OBJECT-TYPE
			SYNTAX Unsigned32
			MAX-ACCESS read-write
			STATUS obsolete
			DESCRIPTION
				"Massage ist inactive!
				
				Description. Priority for dvbDDAmplifierResetFaultFault event"
			::= { dvbDDEventPriorityGeneral 7 }

		
		-- 1.3.6.1.4.1.19831.1.1.1.4.5.1.8
		dvbDDAmplifierFaultPriority OBJECT-TYPE
			SYNTAX Unsigned32
			MAX-ACCESS read-write
			STATUS current
			DESCRIPTION
				"Description. Priority for dvbDDAmplifierFault event"
			::= { dvbDDEventPriorityGeneral 8 }

		
		-- 1.3.6.1.4.1.19831.1.1.1.4.5.1.9
		dvbDDAmplifierWarningPriority OBJECT-TYPE
			SYNTAX Unsigned32
			MAX-ACCESS read-write
			STATUS current
			DESCRIPTION
				"Description. Priority for dvbDDAmplifierWarning event"
			::= { dvbDDEventPriorityGeneral 9 }

		
		-- 1.3.6.1.4.1.19831.1.1.1.4.5.1.10
		dvbDDActiveExciterPriority OBJECT-TYPE
			SYNTAX Unsigned32
			MAX-ACCESS read-write
			STATUS current
			DESCRIPTION
				"Description. Priority for dvbDDActiveExciter event"
			::= { dvbDDEventPriorityGeneral 10 }

		
		-- 1.3.6.1.4.1.19831.1.1.1.4.5.1.11
		dvbDDLocalModePriority OBJECT-TYPE
			SYNTAX Unsigned32
			MAX-ACCESS read-write
			STATUS current
			DESCRIPTION
				"Description. Priority for dvbDDLocalMode event"
			::= { dvbDDEventPriorityGeneral 11 }

		
		-- 1.3.6.1.4.1.19831.1.1.1.4.5.1.12
		dvbDDControlUnitFaultPriority OBJECT-TYPE
			SYNTAX Unsigned32
			MAX-ACCESS read-write
			STATUS current
			DESCRIPTION
				"Description. Priority for dvbDDControlUnitFault event"
			::= { dvbDDEventPriorityGeneral 12 }

		
		-- 1.3.6.1.4.1.19831.1.1.1.4.5.1.13
		dvbDDSwitchOverModePriority OBJECT-TYPE
			SYNTAX Unsigned32
			MAX-ACCESS read-write
			STATUS current
			DESCRIPTION
				"Description. Priority for dvbDDSwitchOverMode event"
			::= { dvbDDEventPriorityGeneral 13 }

		
		-- 1.3.6.1.4.1.19831.1.1.1.4.5.1.14
		dvbDDSwitchOverReadyPriority OBJECT-TYPE
			SYNTAX Unsigned32
			MAX-ACCESS read-write
			STATUS current
			DESCRIPTION
				"Description. Priority for dvbDDSwitchOverReady event"
			::= { dvbDDEventPriorityGeneral 14 }

		
		-- 1.3.6.1.4.1.19831.1.1.1.4.5.1.15
		dvbDDSwitchOverExecutedPriority OBJECT-TYPE
			SYNTAX Unsigned32
			MAX-ACCESS read-write
			STATUS current
			DESCRIPTION
				"Description. Priority for dvbDDSwitchOverExecuted event"
			::= { dvbDDEventPriorityGeneral 15 }

		
		-- 1.3.6.1.4.1.19831.1.1.1.4.5.1.16
		dvbDDSwitchOverFaultPriority OBJECT-TYPE
			SYNTAX Unsigned32
			MAX-ACCESS read-write
			STATUS current
			DESCRIPTION
				"Description. Priority for dvbDDSwitchOverFault event"
			::= { dvbDDEventPriorityGeneral 16 }

		
-- dvb dual drive: ecxiter A event priority
		-- 1.3.6.1.4.1.19831.1.1.1.4.5.2
		dvbDDEventPriorityExciterA OBJECT IDENTIFIER ::= { dvbDDEventPriority 2 }

		
--   
		-- 1.3.6.1.4.1.19831.1.1.1.4.5.2.1
		dvbDDExciterAInput1OKPriority OBJECT-TYPE
			SYNTAX Unsigned32
			MAX-ACCESS read-write
			STATUS current
			DESCRIPTION
				"Description. Priority for dvbDDExciterAInput1OK event"
			::= { dvbDDEventPriorityExciterA 1 }

		
--    
		-- 1.3.6.1.4.1.19831.1.1.1.4.5.2.2
		dvbDDExciterAInput2OKPriority OBJECT-TYPE
			SYNTAX Unsigned32
			MAX-ACCESS read-write
			STATUS current
			DESCRIPTION
				"Description. Priority for dvbDDExciterAInput2OK event"
			::= { dvbDDEventPriorityExciterA 2 }

		
--   
		-- 1.3.6.1.4.1.19831.1.1.1.4.5.2.3
		dvbDDExciterALocalModePriority OBJECT-TYPE
			SYNTAX Unsigned32
			MAX-ACCESS read-write
			STATUS current
			DESCRIPTION
				"Description. Priority for dvbDDExciterALocalMode event"
			::= { dvbDDEventPriorityExciterA 3 }

		
--   
		-- 1.3.6.1.4.1.19831.1.1.1.4.5.2.4
		dvbDDExciterAFaultPriority OBJECT-TYPE
			SYNTAX Unsigned32
			MAX-ACCESS read-write
			STATUS current
			DESCRIPTION
				"Description. Priority for dvbDDExciterAFault event"
			::= { dvbDDEventPriorityExciterA 4 }

		
--  
		-- 1.3.6.1.4.1.19831.1.1.1.4.5.2.5
		dvbDDExciterAWarningPriority OBJECT-TYPE
			SYNTAX Unsigned32
			MAX-ACCESS read-write
			STATUS current
			DESCRIPTION
				"Description. Priority for dvbDDExciterAWarning event"
			::= { dvbDDEventPriorityExciterA 5 }

		
--    
		-- 1.3.6.1.4.1.19831.1.1.1.4.5.2.6
		dvbDDExciterAActiveInputPriority OBJECT-TYPE
			SYNTAX Unsigned32
			MAX-ACCESS read-write
			STATUS current
			DESCRIPTION
				"Description. Priority for dvbDDExciterAActiveInput event"
			::= { dvbDDEventPriorityExciterA 6 }

		
--    
		-- 1.3.6.1.4.1.19831.1.1.1.4.5.2.7
		dvbDDExciterASFNModePriority OBJECT-TYPE
			SYNTAX Unsigned32
			MAX-ACCESS read-write
			STATUS current
			DESCRIPTION
				"Description. Priority for dvbDDExciterASFNMode event"
			::= { dvbDDEventPriorityExciterA 7 }

		
--    
		-- 1.3.6.1.4.1.19831.1.1.1.4.5.2.8
		dvbDDExciterARefFaultPriority OBJECT-TYPE
			SYNTAX Unsigned32
			MAX-ACCESS read-write
			STATUS current
			DESCRIPTION
				"Description. Priority for dvbDDExciterARefFault event"
			::= { dvbDDEventPriorityExciterA 8 }

		
--  
		-- 1.3.6.1.4.1.19831.1.1.1.4.5.2.9
		dvbDDExciterAMutePriority OBJECT-TYPE
			SYNTAX Unsigned32
			MAX-ACCESS read-write
			STATUS current
			DESCRIPTION
				"Description. Priority for dvbDDExciterAMute event"
			::= { dvbDDEventPriorityExciterA 9 }

		
--    
		-- 1.3.6.1.4.1.19831.1.1.1.4.5.2.10
		dvbDDExciterAFaultMIPPriority OBJECT-TYPE
			SYNTAX Unsigned32
			MAX-ACCESS read-write
			STATUS current
			DESCRIPTION
				"Description. Priority for dvbDDExciterAFaultMIP event"
			::= { dvbDDEventPriorityExciterA 10 }

		
--  
		-- 1.3.6.1.4.1.19831.1.1.1.4.5.2.11
		dvbDDExciterAStuffingModePriority OBJECT-TYPE
			SYNTAX Unsigned32
			MAX-ACCESS read-write
			STATUS current
			DESCRIPTION
				"Description. Priority for dvbDDExciterAStuffingMode event"
			::= { dvbDDEventPriorityExciterA 11 }

		
-- dvb dual drive: exciter B event priority
		-- 1.3.6.1.4.1.19831.1.1.1.4.5.3
		dvbDDEventPriorityExciterB OBJECT IDENTIFIER ::= { dvbDDEventPriority 3 }

		
--  
		-- 1.3.6.1.4.1.19831.1.1.1.4.5.3.1
		dvbDDExciterBInput1OKPriority OBJECT-TYPE
			SYNTAX Unsigned32
			MAX-ACCESS read-write
			STATUS current
			DESCRIPTION
				"Description. Priority for dvbDDExciterBInput1OK event"
			::= { dvbDDEventPriorityExciterB 1 }

		
--   
		-- 1.3.6.1.4.1.19831.1.1.1.4.5.3.2
		dvbDDExciterBInput2OKPriority OBJECT-TYPE
			SYNTAX Unsigned32
			MAX-ACCESS read-write
			STATUS current
			DESCRIPTION
				"Description. Priority for dvbDDExciterBInput2OK event"
			::= { dvbDDEventPriorityExciterB 2 }

		
--  
		-- 1.3.6.1.4.1.19831.1.1.1.4.5.3.3
		dvbDDExciterBLocalModePriority OBJECT-TYPE
			SYNTAX Unsigned32
			MAX-ACCESS read-write
			STATUS current
			DESCRIPTION
				"Description. Priority for dvbDDExciterBLocalMode event"
			::= { dvbDDEventPriorityExciterB 3 }

		
--   
		-- 1.3.6.1.4.1.19831.1.1.1.4.5.3.4
		dvbDDExciterBFaultPriority OBJECT-TYPE
			SYNTAX Unsigned32
			MAX-ACCESS read-write
			STATUS current
			DESCRIPTION
				"Description. Priority for dvbDDExciterBFault event"
			::= { dvbDDEventPriorityExciterB 4 }

		
--   
		-- 1.3.6.1.4.1.19831.1.1.1.4.5.3.5
		dvbDDExciterBWarningPriority OBJECT-TYPE
			SYNTAX Unsigned32
			MAX-ACCESS read-write
			STATUS current
			DESCRIPTION
				"Description. Priority for dvbDDExciterBWarning event"
			::= { dvbDDEventPriorityExciterB 5 }

		
--  
		-- 1.3.6.1.4.1.19831.1.1.1.4.5.3.6
		dvbDDExciterBActiveInputPriority OBJECT-TYPE
			SYNTAX Unsigned32
			MAX-ACCESS read-write
			STATUS current
			DESCRIPTION
				"Description. Priority for dvbDDExciterBActiveInput event"
			::= { dvbDDEventPriorityExciterB 6 }

		
--    
		-- 1.3.6.1.4.1.19831.1.1.1.4.5.3.7
		dvbDDExciterBSFNModePriority OBJECT-TYPE
			SYNTAX Unsigned32
			MAX-ACCESS read-write
			STATUS current
			DESCRIPTION
				"Description. Priority for dvbDDExciterBSFNMode event"
			::= { dvbDDEventPriorityExciterB 7 }

		
--    
		-- 1.3.6.1.4.1.19831.1.1.1.4.5.3.8
		dvbDDExciterBRefFaultPriority OBJECT-TYPE
			SYNTAX Unsigned32
			MAX-ACCESS read-write
			STATUS current
			DESCRIPTION
				"Description. Priority for dvbDDExciterBRefFault event"
			::= { dvbDDEventPriorityExciterB 8 }

		
--   
		-- 1.3.6.1.4.1.19831.1.1.1.4.5.3.9
		dvbDDExciterBMutePriority OBJECT-TYPE
			SYNTAX Unsigned32
			MAX-ACCESS read-write
			STATUS current
			DESCRIPTION
				"Description. Priority for dvbDDExciterBMute event"
			::= { dvbDDEventPriorityExciterB 9 }

		
--   
		-- 1.3.6.1.4.1.19831.1.1.1.4.5.3.10
		dvbDDExciterBFaultMIPPriority OBJECT-TYPE
			SYNTAX Unsigned32
			MAX-ACCESS read-write
			STATUS current
			DESCRIPTION
				"Description. Priority for dvbDDExciterBFaultMIP event"
			::= { dvbDDEventPriorityExciterB 10 }

		
--    
		-- 1.3.6.1.4.1.19831.1.1.1.4.5.3.11
		dvbDDExciterBStuffingModePriority OBJECT-TYPE
			SYNTAX Unsigned32
			MAX-ACCESS read-write
			STATUS current
			DESCRIPTION
				"Description. Priority for dvbDDExciterBStuffingMode event"
			::= { dvbDDEventPriorityExciterB 11 }

		
		-- 1.3.6.1.4.1.19831.1.1.1.4.6
		groupsDD OBJECT IDENTIFIER ::= { dvbDualDrive 6 }

		
-- events
		-- 1.3.6.1.4.1.19831.1.1.1.4.6.1
		eventGroupDD NOTIFICATION-GROUP
			NOTIFICATIONS { dvbDDInputPreselectionEvent, dvbDDInputAutomaticEvent, dvbDDPreselectionExciterEvent, dvbDDTransmitterOpModeEvent, dvbDDReserveControlEvent, 
				dvbDDRFPresentEvent, dvbDDAmplifierFaultEvent, dvbDDActiveExciterEvent, dvbDDLocalModeEvent, dvbDDControlUnitFaultEvent, 
				dvbDDSwitchOverModeEvent, dvbDDSwitchOverReadyEvent, dvbDDSwitchOverExecutedEvent, dvbDDSwitchOverFaultEvent, dvbDDExciterAInput1OKEvent, 
				dvbDDExciterAInput2OKEvent, dvbDDExciterALocalModeEvent, dvbDDExciterAFaultEvent, dvbDDExciterAWarningEvent, dvbDDExciterAActiveInputEvent, 
				dvbDDExciterASFNModeEvent, dvbDDExciterARefFaultEvent, dvbDDExciterAMuteEvent, dvbDDExciterAFaultMIPEvent, dvbDDExciterAStuffingModeEvent, 
				dvbDDExciterBInput1OKEvent, dvbDDExciterBInput2OKEvent, dvbDDExciterBLocalModeEvent, dvbDDExciterBFaultEvent, dvbDDExciterBWarningEvent, 
				dvbDDExciterBActiveInputEvent, dvbDDExciterBSFNModeEvent, dvbDDExciterBRefFaultEvent, dvbDDExciterBMuteEvent, dvbDDExciterBFaultMIPEvent, 
				dvbDDExciterBStuffingModeEvent, dvbDDAmplifierWarningEvent }
			STATUS current
			DESCRIPTION 
				"Description."
			::= { groupsDD 1 }

		
-- objecs
		-- 1.3.6.1.4.1.19831.1.1.1.4.6.2
		objectGroupDD OBJECT-GROUP
			OBJECTS { dvbDDInputPreselection, dvbDDInputAutomatic, dvbDDPreselectionExciter, dvbDDTransmitterOpMode, dvbDDReserveControl, 
				dvbDDRFPresent, dvbDDAmplifierFault, dvbDDActiveExciter, dvbDDLocalMode, dvbDDControlUnitFault, 
				dvbDDSwitchOverMode, dvbDDSwitchOverReady, dvbDDSwitchOverExecuted, dvbDDSwitchOverFault, dvbDDExciterAInput1OK, 
				dvbDDExciterAInput2OK, dvbDDExciterALocalMode, dvbDDExciterAFault, dvbDDExciterAWarning, dvbDDExciterAActiveInput, 
				dvbDDExciterASFNMode, dvbDDExciterARefFault, dvbDDExciterAMute, dvbDDExciterAFaultMIP, dvbDDExciterAStuffingMode, 
				dvbDDExciterBInput1OK, dvbDDExciterBInput2OK, dvbDDExciterBLocalMode, dvbDDExciterBFault, dvbDDExciterBWarning, 
				dvbDDExciterBActiveInput, dvbDDExciterBSFNMode, dvbDDExciterBRefFault, dvbDDExciterBMute, dvbDDExciterBFaultMIP, 
				dvbDDExciterBStuffingMode, dvbDDInputPreselectionEnable, dvbDDInputAutomaticEnable, dvbDDPreselectionExciterEnable, dvbDDTransmitterOpModeEnable, 
				dvbDDReserveControlEnable, dvbDDAmplifierFaultEnable, dvbDDActiveExciterEnable, dvbDDLocalModeEnable, dvbDDControlUnitFaultEnable, 
				dvbDDSwitchOverModeEnable, dvbDDSwitchOverReadyEnable, dvbDDSwitchOverExecutedEnable, dvbDDSwitchOverFaultEnable, dvbDDExciterAInput1OKEnable, 
				dvbDDExciterAInput2OKEnable, dvbDDExciterALocalModeEnable, dvbDDExciterAFaultEnable, dvbDDExciterAWarningEnable, dvbDDExciterAActiveInputEnable, 
				dvbDDExciterASFNModeEnable, dvbDDExciterARefFaultEnable, dvbDDExciterAMuteEnable, dvbDDExciterAFaultMIPEnable, dvbDDExciterAStuffingModeEnable, 
				dvbDDExciterBInput1OKEnable, dvbDDExciterBInput2OKEnable, dvbDDExciterBLocalModeEnable, dvbDDExciterBFaultEnable, dvbDDExciterBWarningEnable, 
				dvbDDExciterBActiveInputEnable, dvbDDExciterBSFNModeEnable, dvbDDExciterBRefFaultEnable, dvbDDExciterBMuteEnable, dvbDDExciterBFaultMIPEnable, 
				dvbDDExciterBStuffingModeEnable, dvbDDInputAutomaticPriority, dvbDDPreselectionExciterPriority, dvbDDTransmitterOpModePriority, dvbDDReserveControlPriority, 
				dvbDDRFPresentPriority, dvbDDAmplifierFaultPriority, dvbDDActiveExciterPriority, dvbDDLocalModePriority, dvbDDControlUnitFaultPriority, 
				dvbDDSwitchOverModePriority, dvbDDSwitchOverReadyPriority, dvbDDSwitchOverExecutedPriority, dvbDDSwitchOverFaultPriority, dvbDDExciterAInput1OKPriority, 
				dvbDDExciterAInput2OKPriority, dvbDDExciterALocalModePriority, dvbDDExciterAFaultPriority, dvbDDExciterAWarningPriority, dvbDDExciterAActiveInputPriority, 
				dvbDDExciterASFNModePriority, dvbDDExciterARefFaultPriority, dvbDDExciterAMutePriority, dvbDDExciterAFaultMIPPriority, dvbDDExciterAStuffingModePriority, 
				dvbDDExciterBInput1OKPriority, dvbDDExciterBInput2OKPriority, dvbDDExciterBLocalModePriority, dvbDDExciterBFaultPriority, dvbDDExciterBWarningPriority, 
				dvbDDExciterBActiveInputPriority, dvbDDExciterBSFNModePriority, dvbDDExciterBRefFaultPriority, dvbDDExciterBMutePriority, dvbDDExciterBFaultMIPPriority, 
				dvbDDExciterBStuffingModePriority, dvbDDInputPreselectionPriority, dvbDDAmplifierWarning, dvbDDRFPresentEnable, dvbDDAmplifierWarningPriority, 
				dvbDDAmplifierWarningEnable }
			STATUS current
			DESCRIPTION 
				"Description.dual drive: object group"
			::= { groupsDD 2 }

		
		-- 1.3.6.1.4.1.19831.1.1.1.4.6.3
		eventGroupDDobsolete NOTIFICATION-GROUP
			NOTIFICATIONS { dvbDDResetFaultEvent }
			STATUS obsolete
			DESCRIPTION 
				"Description."
			::= { groupsDD 3 }

		
		-- 1.3.6.1.4.1.19831.1.1.1.4.6.4
		objectGroupDDobsolete OBJECT-GROUP
			OBJECTS { dvbDDResetFault, dvbDDResetFaultEnable, dvbDDResetFaultPriority }
			STATUS obsolete
			DESCRIPTION 
				"Description.Inactive objects"
			::= { groupsDD 4 }

		
		-- 1.3.6.1.4.1.19831.1.1.1.4.7
		complianceDD OBJECT IDENTIFIER ::= { dvbDualDrive 7 }

		
		-- 1.3.6.1.4.1.19831.1.1.1.4.7.1
		dvbDualDriveCompliance MODULE-COMPLIANCE
			STATUS current
			DESCRIPTION 
				"Compliance Statement"
			MODULE -- this module
				MANDATORY-GROUPS { eventGroupDD, objectGroupDD }
			::= { complianceDD 1 }

		
	
	END

--
-- IRT-DVBT-DUALDRIVE-MIB.my
--
