ACOS-SLB-SSL-JA4-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		slbSslJa4Module MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "slbSslJa4Module OID for ACOS"
				::=  {  acosSchema 315 }

sslJa4		 OBJECT IDENTIFIER ::= { slbSslJa4Module 1}

sslJa4OperRecordTable OBJECT-TYPE
	 SYNTAX SEQUENCE OF SslJa4OperRecordEntry
	 MAX-ACCESS not-accessible
	 STATUS current
	 DESCRIPTION
		 "Show SSL JA4 from object 'slb.ssl-ja4'"
	::= {sslJa4 2}

sslJa4OperRecordEntry OBJECT-TYPE
	SYNTAX SslJa4OperRecordEntry
	MAX-ACCESS not-accessible
	STATUS current
	DESCRIPTION
		"The sslJa4OperRecord entry:record"
	INDEX {
		sslJa4OperRecordSlotId,
		sslJa4OperRecordRecordListId
	}
	::= { sslJa4OperRecordTable 1}

SslJa4OperRecordEntry ::=
	SEQUENCE {
		sslJa4OperRecordSlotId Integer32,
		sslJa4OperRecordRecordListId Integer32,
		sslJa4OperRecordAddrV4	DisplayString,
		sslJa4OperRecordAddrV6	DisplayString,
		sslJa4OperRecordAmount	Integer32
	}

sslJa4OperRecordSlotId OBJECT-TYPE
	SYNTAX Integer32
	MAX-ACCESS read-only
	STATUS current
	DESCRIPTION
		""
	::= { sslJa4OperRecordEntry 1}

sslJa4OperRecordRecordListId OBJECT-TYPE
	SYNTAX Integer32
	MAX-ACCESS read-only
	STATUS current
	DESCRIPTION
		""
	::= { sslJa4OperRecordEntry 2}

sslJa4OperRecordAddrV4 OBJECT-TYPE
	SYNTAX DisplayString
	MAX-ACCESS read-only
	STATUS current
	DESCRIPTION
		"addr-v4"
	::= { sslJa4OperRecordEntry 3}

sslJa4OperRecordAddrV6 OBJECT-TYPE
	SYNTAX DisplayString
	MAX-ACCESS read-only
	STATUS current
	DESCRIPTION
		"addr-v6"
	::= { sslJa4OperRecordEntry 4}

sslJa4OperRecordAmount OBJECT-TYPE
	SYNTAX Integer32
	MAX-ACCESS read-only
	STATUS current
	DESCRIPTION
		"amount"
	::= { sslJa4OperRecordEntry 5}

END
