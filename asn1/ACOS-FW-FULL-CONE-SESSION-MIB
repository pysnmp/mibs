ACOS-FW-FULL-CONE-SESSION-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		fwFullConeSessionModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "fwFullConeSessionModule OID for ACOS"
				::=  {  acosSchema 485 }

fullConeSession		 OBJECT IDENTIFIER ::= { fwFullConeSessionModule 1}

fullConeSessionOperTable OBJECT-TYPE
	 SYNTAX SEQUENCE OF FullConeSessionOperEntry
	 MAX-ACCESS not-accessible
	 STATUS current
	 DESCRIPTION
		 "Full Cone Sessions from object 'fw.full-cone-session'"
	::= {fullConeSession 2}

fullConeSessionOperEntry OBJECT-TYPE
	SYNTAX FullConeSessionOperEntry
	MAX-ACCESS not-accessible
	STATUS current
	DESCRIPTION
		"The fullConeSessionOper entry"
	INDEX {
		fullConeSessionOperSlotId
	}
	::= { fullConeSessionOperTable 1 }

FullConeSessionOperEntry ::=
	SEQUENCE {
		fullConeSessionOperSlotId Integer32,
		fullConeSessionOperTotal	 Integer32,
		fullConeSessionOperIpv4Addr	 DisplayString,
		fullConeSessionOperIpv6Addr	 DisplayString
	}

fullConeSessionOperSlotId OBJECT-TYPE
	 SYNTAX Integer32
	 MAX-ACCESS read-only
	 STATUS current
	 DESCRIPTION
		 ""
	::= { fullConeSessionOperEntry 1 }

fullConeSessionOperTotal OBJECT-TYPE
	 SYNTAX Integer32
	 MAX-ACCESS read-only
	 STATUS current
	 DESCRIPTION
		 "total"
	::= { fullConeSessionOperEntry 2 }

fullConeSessionOperIpv4Addr OBJECT-TYPE
	 SYNTAX DisplayString
	 MAX-ACCESS read-only
	 STATUS current
	 DESCRIPTION
		 "ipv4-addr"
	::= { fullConeSessionOperEntry 3 }

fullConeSessionOperIpv6Addr OBJECT-TYPE
	 SYNTAX DisplayString
	 MAX-ACCESS read-only
	 STATUS current
	 DESCRIPTION
		 "ipv6-addr"
	::= { fullConeSessionOperEntry 4 }

fullConeSessionOperSessionListTable OBJECT-TYPE
	 SYNTAX SEQUENCE OF FullConeSessionOperSessionListEntry
	 MAX-ACCESS not-accessible
	 STATUS current
	 DESCRIPTION
		 "Full Cone Sessions from object 'fw.full-cone-session'"
	::= {fullConeSession 3}

fullConeSessionOperSessionListEntry OBJECT-TYPE
	SYNTAX FullConeSessionOperSessionListEntry
	MAX-ACCESS not-accessible
	STATUS current
	DESCRIPTION
		"The fullConeSessionOperSessionList entry:session-list"
	INDEX {
		fullConeSessionOperSessionListSlotId,
		fullConeSessionOperSessionListSessionListListId
	}
	::= { fullConeSessionOperSessionListTable 1}

FullConeSessionOperSessionListEntry ::=
	SEQUENCE {
		fullConeSessionOperSessionListSlotId Integer32,
		fullConeSessionOperSessionListSessionListListId Integer32,
		fullConeSessionOperSessionListProtocol	DisplayString,
		fullConeSessionOperSessionListInsideAddress	DisplayString,
		fullConeSessionOperSessionListInsidePort	Integer32,
		fullConeSessionOperSessionListOutbound	Integer32,
		fullConeSessionOperSessionListInbound	Integer32,
		fullConeSessionOperSessionListCpu	Integer32,
		fullConeSessionOperSessionListAge	DisplayString
	}

fullConeSessionOperSessionListSlotId OBJECT-TYPE
	SYNTAX Integer32
	MAX-ACCESS read-only
	STATUS current
	DESCRIPTION
		""
	::= { fullConeSessionOperSessionListEntry 1}

fullConeSessionOperSessionListSessionListListId OBJECT-TYPE
	SYNTAX Integer32
	MAX-ACCESS read-only
	STATUS current
	DESCRIPTION
		""
	::= { fullConeSessionOperSessionListEntry 2}

fullConeSessionOperSessionListProtocol OBJECT-TYPE
	SYNTAX DisplayString
	MAX-ACCESS read-only
	STATUS current
	DESCRIPTION
		"protocol"
	::= { fullConeSessionOperSessionListEntry 3}

fullConeSessionOperSessionListInsideAddress OBJECT-TYPE
	SYNTAX DisplayString
	MAX-ACCESS read-only
	STATUS current
	DESCRIPTION
		"inside-address"
	::= { fullConeSessionOperSessionListEntry 4}

fullConeSessionOperSessionListInsidePort OBJECT-TYPE
	SYNTAX Integer32
	MAX-ACCESS read-only
	STATUS current
	DESCRIPTION
		"inside-port"
	::= { fullConeSessionOperSessionListEntry 5}

fullConeSessionOperSessionListOutbound OBJECT-TYPE
	SYNTAX Integer32
	MAX-ACCESS read-only
	STATUS current
	DESCRIPTION
		"outbound"
	::= { fullConeSessionOperSessionListEntry 6}

fullConeSessionOperSessionListInbound OBJECT-TYPE
	SYNTAX Integer32
	MAX-ACCESS read-only
	STATUS current
	DESCRIPTION
		"inbound"
	::= { fullConeSessionOperSessionListEntry 7}

fullConeSessionOperSessionListCpu OBJECT-TYPE
	SYNTAX Integer32
	MAX-ACCESS read-only
	STATUS current
	DESCRIPTION
		"cpu"
	::= { fullConeSessionOperSessionListEntry 8}

fullConeSessionOperSessionListAge OBJECT-TYPE
	SYNTAX DisplayString
	MAX-ACCESS read-only
	STATUS current
	DESCRIPTION
		"age"
	::= { fullConeSessionOperSessionListEntry 9}

END
