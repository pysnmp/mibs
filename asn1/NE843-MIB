NE843-MIB DEFINITIONS ::= BEGIN
IMPORTS
     enterprises, MODULE-IDENTITY, OBJECT-TYPE, Integer32, NOTIFICATION-TYPE 
         FROM SNMPv2-SMI
     DisplayString
         FROM SNMPv2-TC;

teps                   OBJECT IDENTIFIER ::= { enterprises 10520 }
controllermibs         OBJECT IDENTIFIER ::= { teps 2 }
release                OBJECT IDENTIFIER ::= { controllermibs 1 }
prototypes             OBJECT IDENTIFIER ::= { controllermibs 2 }

ne843 MODULE-IDENTITY
   LAST-UPDATED "201601121648Z"
   ORGANIZATION "GE Power Electronics, Inc."
   CONTACT-INFO "Chris Brooke - Power Systems

                 Phone: +1 972 244 9288

                 Postal: Power Systems
                         601 Shiloh Road
                         Plano, TX 75074
                         USA"

   DESCRIPTION "MIB for NE843 Power System."
   
   REVISION "201601121648Z"
   DESCRIPTION "Added DPN, and DBY"
   
   REVISION "201510301950Z"
   DESCRIPTION "Added PIC, PCM, PVM, PTM and PCS. Add integer representation for some variables"
   
   REVISION "201503272138Z"
   DESCRIPTION "Added 3-Phase rectifier voltages and currents"

   REVISION "201412152301Z"
   DESCRIPTION "Added Bulk Data Report"

   REVISION "201410222033Z"
   DESCRIPTION "Added IPV6 Parameters"

   REVISION "201406101441Z"
   DESCRIPTION "Added Trap/Alarm, change name of inverter plant"

   REVISION "201405211844Z"
   DESCRIPTION "Added High Temperature Load Disconnect"

   REVISION "201403181952Z" 
   DESCRIPTION "Added Inverters, ECO Priority, and ORing Fet Parameters"

   REVISION "201210032143Z"
   DESCRIPTION "Add more objects and updates from CP841 and Millennium 2"


   REVISION "201006281408Z"
   DESCRIPTION "Add more objects to traps"

   REVISION "200906181832Z"
   DESCRIPTION "Switch to unique object names"

   REVISION "200905141624Z"
   DESCRIPTION "Add updates from CP841 and IEPSO"

   REVISION "200704031635Z"
   DESCRIPTION "Initial release"

   ::= { release 3 }

--
-- object ne843Dc1
--

ne843Dc1 OBJECT IDENTIFIER  ::= { ne843  1 }

ne843Dc1Ide OBJECT-TYPE
SYNTAX      DisplayString
MAX-ACCESS  read-only
STATUS      current
DESCRIPTION
"Identifier"
 ::= { ne843Dc1  1 }

ne843Dc1Des OBJECT-TYPE
SYNTAX      DisplayString
MAX-ACCESS  read-write
STATUS      current
DESCRIPTION
"Description"
 ::= { ne843Dc1  2 }

ne843Dc1Typ OBJECT-TYPE
SYNTAX      DisplayString
MAX-ACCESS  read-only
STATUS      current
DESCRIPTION
"Type"
 ::= { ne843Dc1  3 }

ne843Dc1Vdc OBJECT-TYPE
SYNTAX      Integer32
UNITS       "mV"
MAX-ACCESS  read-only
STATUS      current
DESCRIPTION
"Voltage (mV)"
 ::= { ne843Dc1  4 }

ne843Dc1Adc OBJECT-TYPE
SYNTAX      Integer32
UNITS       "Amps"
MAX-ACCESS  read-only
STATUS      current
DESCRIPTION
"Current (Amps)"
 ::= { ne843Dc1  5 }

ne843Dc1Cap OBJECT-TYPE
SYNTAX      Integer32
UNITS       "Amps"
MAX-ACCESS  read-only
STATUS      current
DESCRIPTION
"Total Installed Rectifier Capacity (Amps)"
 ::= { ne843Dc1  6 }

ne843Dc1Olcap OBJECT-TYPE
SYNTAX      Integer32
UNITS       "Amps"
MAX-ACCESS  read-only
STATUS      current
DESCRIPTION
"Total On-line Rectifier Capacity (Amps)"
 ::= { ne843Dc1  7 }

ne843Dc1Trd OBJECT-TYPE
SYNTAX      Integer32
UNITS       "Amps"
MAX-ACCESS  read-only
STATUS      current
DESCRIPTION
"Total Rectifier Drain (Amps)"
 ::= { ne843Dc1  8 }

ne843Dc1Sht OBJECT-TYPE
SYNTAX      DisplayString
MAX-ACCESS  read-write
STATUS      current
DESCRIPTION
"Centralized Plant Shunt Type
Values:
NONE,
BATTERY,
LOAD
"
 ::= { ne843Dc1  9 }

ne843Dc1Sha OBJECT-TYPE
SYNTAX      Integer32
UNITS       "Amps"
MAX-ACCESS  read-write
STATUS      current
DESCRIPTION
"Centralized Plant Shunt Size (Amps)"
 ::= { ne843Dc1  10 }

ne843Dc1Stt OBJECT-TYPE
SYNTAX      DisplayString
MAX-ACCESS  read-write
STATUS      current
DESCRIPTION
"State
Values:
FLOAT,
BOOST
"
 ::= { ne843Dc1  11 }

ne843Dc1Bod OBJECT-TYPE
SYNTAX      DisplayString
MAX-ACCESS  read-only
STATUS      current
DESCRIPTION
"Battery On Discharge"
 ::= { ne843Dc1  12 }

ne843Dc1Rss OBJECT-TYPE
SYNTAX      INTEGER {
off(0),
on(1)
}
MAX-ACCESS  read-write
STATUS      current
DESCRIPTION
"Rectifier Restart
Values:
off(0),
on(1)
"
 ::= { ne843Dc1  13 }

ne843Dc1Rsq OBJECT-TYPE
SYNTAX      INTEGER {
disable(0),
enable(1)
}
MAX-ACCESS  read-write
STATUS      current
DESCRIPTION
"Rectifier Sequencing
Values:
disable(0),
enable(1)
"
 ::= { ne843Dc1  14 }

ne843Dc1Ron OBJECT-TYPE
SYNTAX      Integer32
MAX-ACCESS  read-write
STATUS      current
DESCRIPTION
"External Standby"
 ::= { ne843Dc1  15 }

ne843Dc1Rot OBJECT-TYPE
SYNTAX      Integer32(20000..25000|40000..50000)
UNITS       "mV"
MAX-ACCESS  read-write
STATUS      current
DESCRIPTION
"All Rectifier On Threshold (mV)"
 ::= { ne843Dc1  16 }

ne843Dc1Nst OBJECT-TYPE
SYNTAX      Integer32
MAX-ACCESS  read-only
STATUS      current
DESCRIPTION
"Number of Strings"
 ::= { ne843Dc1  17 }

ne843Dc1Cps OBJECT-TYPE
SYNTAX      Integer32
MAX-ACCESS  read-only
STATUS      current
DESCRIPTION
"Cells per String"
 ::= { ne843Dc1  18 }

ne843Dc1Bty OBJECT-TYPE
SYNTAX      DisplayString
MAX-ACCESS  read-only
STATUS      current
DESCRIPTION
"Battery Type"
 ::= { ne843Dc1  19 }

ne843Dc1Isd OBJECT-TYPE
SYNTAX      INTEGER {
disable(0),
enable(1)
}
MAX-ACCESS  read-write
STATUS      current
DESCRIPTION
"Imminent Shutdown Enable
Values:
disable(0),
enable(1)
"
 ::= { ne843Dc1  20 }

ne843Dc1Rtm OBJECT-TYPE
SYNTAX      DisplayString
MAX-ACCESS  read-only
STATUS      current
DESCRIPTION
"Reserve Time"
 ::= { ne843Dc1  21 }

ne843Dc1Scap OBJECT-TYPE
SYNTAX      Integer32
UNITS       "Amps"
MAX-ACCESS  read-only
STATUS      current
DESCRIPTION
"String Capacity (Amps)"
 ::= { ne843Dc1  22 }

ne843Dc1Mls OBJECT-TYPE
SYNTAX      INTEGER {
disable(0),
enable(1)
}
MAX-ACCESS  read-write
STATUS      current
DESCRIPTION
"All Shunts Monitored
Values:
disable(0),
enable(1)
"
 ::= { ne843Dc1  23 }

ne843Dc1Amj OBJECT-TYPE
SYNTAX      DisplayString
MAX-ACCESS  read-only
STATUS      current
DESCRIPTION
"Auxiliary Fuse Major
Value:
Alarm report from AMJ1
"
 ::= { ne843Dc1  24 }

ne843Dc1Vsf OBJECT-TYPE
SYNTAX      DisplayString
MAX-ACCESS  read-only
STATUS      current
DESCRIPTION
"Sense/Control Fuse
Value:
Alarm report from VSF1
"
 ::= { ne843Dc1  25 }

ne843Dc1Osa OBJECT-TYPE
SYNTAX      DisplayString
MAX-ACCESS  read-only
STATUS      current
DESCRIPTION
"Open String
Value:
Alarm report from OSA1
"
 ::= { ne843Dc1  26 }

ne843Dc1Zid OBJECT-TYPE
SYNTAX      DisplayString
MAX-ACCESS  read-only
STATUS      current
DESCRIPTION
"ID Not Configured
Value:
Alarm report from ZID1
"
 ::= { ne843Dc1  27 }

ne843Dc1Tpa OBJECT-TYPE
SYNTAX      DisplayString
MAX-ACCESS  read-only
STATUS      current
DESCRIPTION
"Thermal Probe Alarm
Value:
Alarm report from TPA1
"
 ::= { ne843Dc1  28 }

ne843Dc1Vmf OBJECT-TYPE
SYNTAX      DisplayString
MAX-ACCESS  read-only
STATUS      current
DESCRIPTION
"Voltage Module Fail
Value:
Alarm report from VMF1
"
 ::= { ne843Dc1  29 }

ne843Dc1Cma OBJECT-TYPE
SYNTAX      DisplayString
MAX-ACCESS  read-only
STATUS      current
DESCRIPTION
"Minor Communication Failure
Value:
Alarm report from CMA1
"
 ::= { ne843Dc1  30 }

ne843Dc1Mcm OBJECT-TYPE
SYNTAX      DisplayString
MAX-ACCESS  read-only
STATUS      current
DESCRIPTION
"Major Communication Failure
Value:
Alarm report from MCM1
"
 ::= { ne843Dc1  31 }

ne843Dc1Epo OBJECT-TYPE
SYNTAX      DisplayString
MAX-ACCESS  read-only
STATUS      current
DESCRIPTION
"Emergency Power Off
Value:
Alarm report from EPO1
"
 ::= { ne843Dc1  32 }

ne843Dc1Icr OBJECT-TYPE
SYNTAX      DisplayString
MAX-ACCESS  read-only
STATUS      current
DESCRIPTION
"Incompatible Rectifier
Value:
Alarm report from ICR1
"
 ::= { ne843Dc1  33 }

ne843Dc1Rfa OBJECT-TYPE
SYNTAX      DisplayString
MAX-ACCESS  read-only
STATUS      current
DESCRIPTION
"Rectifier Fail
Value:
Alarm report from RFA1
"
 ::= { ne843Dc1  34 }

ne843Dc1Acf OBJECT-TYPE
SYNTAX      DisplayString
MAX-ACCESS  read-only
STATUS      current
DESCRIPTION
"AC Fail
Value:
Alarm report from ACF1
"
 ::= { ne843Dc1  35 }

ne843Dc1Man OBJECT-TYPE
SYNTAX      DisplayString
MAX-ACCESS  read-only
STATUS      current
DESCRIPTION
"Manual Off
Value:
Alarm report from MAN1
"
 ::= { ne843Dc1  36 }

ne843Dc1Did OBJECT-TYPE
SYNTAX      DisplayString
MAX-ACCESS  read-only
STATUS      current
DESCRIPTION
"ID Conflict
Value:
Alarm report from DID1
"
 ::= { ne843Dc1  37 }

ne843Dc1Clm OBJECT-TYPE
SYNTAX      DisplayString
MAX-ACCESS  read-only
STATUS      current
DESCRIPTION
"Rectifier Current Limit
Value:
Alarm report from CLM1
"
 ::= { ne843Dc1  38 }

ne843Dc1Rfn OBJECT-TYPE
SYNTAX      DisplayString
MAX-ACCESS  read-only
STATUS      current
DESCRIPTION
"Rectifier Fan Failure
Value:
Alarm report from RFN1
"
 ::= { ne843Dc1  39 }

ne843Dc1Vla OBJECT-TYPE
SYNTAX      DisplayString
MAX-ACCESS  read-only
STATUS      current
DESCRIPTION
"Very Low Voltage
Value:
Alarm report from VLA1
"
 ::= { ne843Dc1  40 }

ne843Dc1Mfa OBJECT-TYPE
SYNTAX      DisplayString
MAX-ACCESS  read-only
STATUS      current
DESCRIPTION
"Multiple Rectifier Fail
Value:
Alarm report from MFA1
"
 ::= { ne843Dc1  41 }

ne843Dc1Rtl OBJECT-TYPE
SYNTAX      DisplayString
MAX-ACCESS  read-only
STATUS      current
DESCRIPTION
"Reserve Time Low
Value:
Alarm report from RTL1
"
 ::= { ne843Dc1  42 }

ne843Dc1Rrtl OBJECT-TYPE
SYNTAX      DisplayString
MAX-ACCESS  read-only
STATUS      current
DESCRIPTION
"Real-time Reserve Time Low
Value:
Alarm report from RRTL1
"
 ::= { ne843Dc1  43 }

ne843Dc1Rls OBJECT-TYPE
SYNTAX      DisplayString
MAX-ACCESS  read-only
STATUS      current
DESCRIPTION
"Redundancy Loss
Value:
Alarm report from RLS1
"
 ::= { ne843Dc1  44 }

ne843Dc1Mman OBJECT-TYPE
SYNTAX      DisplayString
MAX-ACCESS  read-only
STATUS      current
DESCRIPTION
"Multiple Manual Off
Value:
Alarm report from MMAN1
"
 ::= { ne843Dc1  45 }

ne843Dc1Macf OBJECT-TYPE
SYNTAX      DisplayString
MAX-ACCESS  read-only
STATUS      current
DESCRIPTION
"Multiple AC Failure
Value:
Alarm report from MACF1
"
 ::= { ne843Dc1  46 }

ne843Dc1Bda OBJECT-TYPE
SYNTAX      DisplayString
MAX-ACCESS  read-only
STATUS      current
DESCRIPTION
"Battery On Discharge
Value:
Alarm report from BDA1
"
 ::= { ne843Dc1  47 }

ne843Dc1Hva OBJECT-TYPE
SYNTAX      DisplayString
MAX-ACCESS  read-only
STATUS      current
DESCRIPTION
"High Voltage
Value:
Alarm report from HVA1
"
 ::= { ne843Dc1  48 }

ne843Dc1Hfv OBJECT-TYPE
SYNTAX      DisplayString
MAX-ACCESS  read-only
STATUS      current
DESCRIPTION
"High Float Voltage
Value:
Alarm report from HFV1
"
 ::= { ne843Dc1  49 }

ne843Dc1Bdt OBJECT-TYPE
SYNTAX      DisplayString
MAX-ACCESS  read-only
STATUS      current
DESCRIPTION
"BD Duration"
 ::= { ne843Dc1  50 }

ne843Dc1Ems OBJECT-TYPE
SYNTAX      DisplayString
MAX-ACCESS  read-only
STATUS      current
DESCRIPTION
"Energy Management State"
 ::= { ne843Dc1  51 }

ne843Dc1Eme OBJECT-TYPE
SYNTAX      INTEGER {
disable(0),
enable(1)
}
MAX-ACCESS  read-write
STATUS      current
DESCRIPTION
"Energy Management Enable
Values:
disable(0),
enable(1)
"
 ::= { ne843Dc1  52 }

ne843Dc1Emt OBJECT-TYPE
SYNTAX      Integer32(20..95)
UNITS       "%"
MAX-ACCESS  read-write
STATUS      current
DESCRIPTION
"Efficiency Target (%)"
 ::= { ne843Dc1  53 }

ne843Dc1Emo OBJECT-TYPE
SYNTAX      Integer32(25..100)
UNITS       "%"
MAX-ACCESS  read-write
STATUS      current
DESCRIPTION
"Efficiency Rectifier Turn On Threshold (%)"
 ::= { ne843Dc1  54 }

ne843Dc1Poc OBJECT-TYPE
SYNTAX      DisplayString
UNITS       "%"
MAX-ACCESS  read-only
STATUS      current
DESCRIPTION
"Percent of Charge (%)"
 ::= { ne843Dc1  55 }

ne843Dc1Emd OBJECT-TYPE
SYNTAX      DisplayString
MAX-ACCESS  read-only
STATUS      current
DESCRIPTION
"Energy Management Disabled
Value:
Alarm report from EMD1
"
 ::= { ne843Dc1  56 }

ne843Dc1Pfs OBJECT-TYPE
SYNTAX      DisplayString
MAX-ACCESS  read-only
STATUS      current
DESCRIPTION
"Thermal Probe Fail Safe
Value:
Alarm report from PFS1
"
 ::= { ne843Dc1  57 }

ne843Dc1Rif OBJECT-TYPE
SYNTAX      DisplayString
MAX-ACCESS  read-only
STATUS      current
DESCRIPTION
"Rectifier Internal Fault
Value:
Alarm report from RIF1
"
 ::= { ne843Dc1  58 }

ne843Dc1Lsf OBJECT-TYPE
SYNTAX      DisplayString
MAX-ACCESS  read-only
STATUS      current
DESCRIPTION
"Load Share Fail
Value:
Alarm report from LSF1
"
 ::= { ne843Dc1  59 }

ne843Dc1Emi OBJECT-TYPE
SYNTAX      Integer32(0..30)
UNITS       "Minutes"
MAX-ACCESS  read-write
STATUS      current
DESCRIPTION
"Efficiency Initial Delay (Minutes)"
 ::= { ne843Dc1  60 }

ne843Dc1Emw OBJECT-TYPE
SYNTAX      Integer32(0..30)
UNITS       "Minutes"
MAX-ACCESS  read-write
STATUS      current
DESCRIPTION
"Efficiency Turn Off Delay (Minutes)"
 ::= { ne843Dc1  61 }

ne843Dc1Aseq OBJECT-TYPE
SYNTAX      INTEGER {
disable(0),
enable(1)
}
MAX-ACCESS  read-write
STATUS      current
DESCRIPTION
"Automatic Sequencing
Values:
disable(0),
enable(1)
"
 ::= { ne843Dc1  62 }

ne843Dc1Isy OBJECT-TYPE
SYNTAX      Integer32(2..300)
MAX-ACCESS  read-write
STATUS      current
DESCRIPTION
"Imminent Shutdown Delay"
 ::= { ne843Dc1  63 }

ne843Dc1Bofe OBJECT-TYPE
SYNTAX      INTEGER {
disable(0),
enable(1)
}
MAX-ACCESS  read-write
STATUS      current
DESCRIPTION
"Backup ORing FET Test Enable
Values:
disable(0),
enable(1)
"
 ::= { ne843Dc1  64 }

ne843Dc1Bof OBJECT-TYPE
SYNTAX      DisplayString
MAX-ACCESS  read-only
STATUS      current
DESCRIPTION
"Rectifier ORing FET Fault
Value:
Alarm report from BOF1
"
 ::= { ne843Dc1  65 }

ne843Dc1Sof OBJECT-TYPE
SYNTAX      DisplayString
MAX-ACCESS  read-only
STATUS      current
DESCRIPTION
"Rectifier Shorted ORing FET
Value:
Alarm report from SOF1
"
 ::= { ne843Dc1  66 }

ne843Dc1Der OBJECT-TYPE
SYNTAX      DisplayString
MAX-ACCESS  read-only
STATUS      current
DESCRIPTION
"Rectifier Under Voltage
Value:
Alarm report from DER1
"
 ::= { ne843Dc1  67 }

ne843Dc1Pmf OBJECT-TYPE
SYNTAX      DisplayString
MAX-ACCESS  read-only
STATUS      current
DESCRIPTION
"Probe Minimum Fail
Value:
Alarm report from PMF1
"
 ::= { ne843Dc1  68 }

ne843Dc1Faja OBJECT-TYPE
SYNTAX      DisplayString
MAX-ACCESS  read-only
STATUS      current
DESCRIPTION
"Distribution Fuse A
Value:
Alarm report from FAJA1
"
 ::= { ne843Dc1  69 }

ne843Dc1Buht OBJECT-TYPE
SYNTAX      DisplayString
MAX-ACCESS  read-only
STATUS      current
DESCRIPTION
"Bus Hi Temp
Value:
Alarm report from BUHT1
"
 ::= { ne843Dc1  70 }

ne843Dc1Buvht OBJECT-TYPE
SYNTAX      DisplayString
MAX-ACCESS  read-only
STATUS      current
DESCRIPTION
"Bus Very Hi Temp
Value:
Alarm report from BUVHT1
"
 ::= { ne843Dc1  71 }

ne843Dc1Btha OBJECT-TYPE
SYNTAX      DisplayString
MAX-ACCESS  read-only
STATUS      current
DESCRIPTION
"Batt Hi Temp
Value:
Alarm report from BTHA1
"
 ::= { ne843Dc1  72 }

ne843Dc1Btvh OBJECT-TYPE
SYNTAX      DisplayString
MAX-ACCESS  read-only
STATUS      current
DESCRIPTION
"Batt Very Hi Temp
Value:
Alarm report from BTVH1
"
 ::= { ne843Dc1  73 }

ne843Dc1Btla OBJECT-TYPE
SYNTAX      DisplayString
MAX-ACCESS  read-only
STATUS      current
DESCRIPTION
"Batt Low Temp
Value:
Alarm report from BTLA1
"
 ::= { ne843Dc1  74 }

ne843Dc1Btvl OBJECT-TYPE
SYNTAX      DisplayString
MAX-ACCESS  read-only
STATUS      current
DESCRIPTION
"Batt Very Low Temp
Value:
Alarm report from BTVL1
"
 ::= { ne843Dc1  75 }

ne843Dc1Laht OBJECT-TYPE
SYNTAX      DisplayString
MAX-ACCESS  read-only
STATUS      current
DESCRIPTION
"Local Amb. Hi Temp
Value:
Alarm report from LAHT1
"
 ::= { ne843Dc1  76 }

ne843Dc1Lalt OBJECT-TYPE
SYNTAX      DisplayString
MAX-ACCESS  read-only
STATUS      current
DESCRIPTION
"Local Amb. Low Temp
Value:
Alarm report from LALT1
"
 ::= { ne843Dc1  77 }

ne843Dc1Raht OBJECT-TYPE
SYNTAX      DisplayString
MAX-ACCESS  read-only
STATUS      current
DESCRIPTION
"Remote Amb. Hi Temp
Value:
Alarm report from RAHT
"
 ::= { ne843Dc1  78 }

ne843Dc1Ravht OBJECT-TYPE
SYNTAX      DisplayString
MAX-ACCESS  read-only
STATUS      current
DESCRIPTION
"Remote Amb. Very Hi Temp
Value:
Alarm report from RAVHT1
"
 ::= { ne843Dc1  79 }

ne843Dc1Ralt OBJECT-TYPE
SYNTAX      DisplayString
MAX-ACCESS  read-only
STATUS      current
DESCRIPTION
"Remote Amb. Low Temp
Value:
Alarm report from RALT1
"
 ::= { ne843Dc1  80 }

ne843Dc1Vlva OBJECT-TYPE
SYNTAX      DisplayString
MAX-ACCESS  read-only
STATUS      current
DESCRIPTION
"VA Power Loss
Value:
Alarm report from VLVA1
"
 ::= { ne843Dc1  81 }

ne843Dc1Vlvb OBJECT-TYPE
SYNTAX      DisplayString
MAX-ACCESS  read-only
STATUS      current
DESCRIPTION
"VB Power Loss
Value:
Alarm report from VLBB1
"
 ::= { ne843Dc1  82 }

ne843Dc1Ovla OBJECT-TYPE
SYNTAX      DisplayString
MAX-ACCESS  read-only
STATUS      current
DESCRIPTION
"IA Overload
Value:
Alarm report from OVLA1
"
 ::= { ne843Dc1  83 }

ne843Dc1Ovlb OBJECT-TYPE
SYNTAX      DisplayString
MAX-ACCESS  read-only
STATUS      current
DESCRIPTION
"IB Overload
Value:
Alarm report from OVLB1
"
 ::= { ne843Dc1  84 }

ne843Dc1Pcaux OBJECT-TYPE
SYNTAX      DisplayString
MAX-ACCESS  read-only
STATUS      current
DESCRIPTION
"PIC Auxiliary
Value:
Alarm report from PCAUX1
"
 ::= { ne843Dc1  85 }

ne843Dc1Slot OBJECT-TYPE
SYNTAX      DisplayString
MAX-ACCESS  read-only
STATUS      current
DESCRIPTION
"PIC Slot
Value:
Alarm report from SLOT1
"
 ::= { ne843Dc1  86 }

ne843Dc1Bod1 OBJECT-TYPE
SYNTAX      INTEGER {
inactive(0),
active(1)
}
MAX-ACCESS  read-only
STATUS      current
DESCRIPTION
"Battery On Discharge
Values:
inactive(0),
active(1)
"
 ::= { ne843Dc1  87 }

ne843Dc1Bdt1 OBJECT-TYPE
SYNTAX      Integer32
UNITS       "Seconds"
MAX-ACCESS  read-only
STATUS      current
DESCRIPTION
"BD Duration (Seconds)"
 ::= { ne843Dc1  88 }

ne843Dc1Poc1 OBJECT-TYPE
SYNTAX      Integer32(0..100)
UNITS       "%"
MAX-ACCESS  read-only
STATUS      current
DESCRIPTION
"Percent of Charge (%)"
 ::= { ne843Dc1  89 }

ne843Dc1Fajb OBJECT-TYPE
SYNTAX      DisplayString
MAX-ACCESS  read-only
STATUS      current
DESCRIPTION
"Distribution Fuse B
Value:
Alarm report from FAJB1
"
 ::= { ne843Dc1  90 }

ne843Dc1Smw OBJECT-TYPE
SYNTAX      DisplayString
MAX-ACCESS  read-only
STATUS      current
DESCRIPTION
"Shunt Mis-wired
Value:
Alarm report from SMW1
"
 ::= { ne843Dc1  91 }

ne843Dc1Cca OBJECT-TYPE
SYNTAX      DisplayString
MAX-ACCESS  read-only
STATUS      current
DESCRIPTION
"Circuit Assignment
Value:
Alarm report from CCA1
"
 ::= { ne843Dc1  92 }


--
-- object ne843Ps1
--

ne843Ps1 OBJECT IDENTIFIER  ::= { ne843  2 }

ne843Ps1Ide OBJECT-TYPE
SYNTAX      DisplayString
MAX-ACCESS  read-only
STATUS      current
DESCRIPTION
"Identifier"
 ::= { ne843Ps1  1 }

ne843Ps1Des OBJECT-TYPE
SYNTAX      DisplayString
MAX-ACCESS  read-write
STATUS      current
DESCRIPTION
"Description"
 ::= { ne843Ps1  2 }

ne843Ps1Sid OBJECT-TYPE
SYNTAX      DisplayString
MAX-ACCESS  read-write
STATUS      current
DESCRIPTION
"Site ID"
 ::= { ne843Ps1  3 }

ne843Ps1Sde OBJECT-TYPE
SYNTAX      DisplayString
MAX-ACCESS  read-write
STATUS      current
DESCRIPTION
"Site Description"
 ::= { ne843Ps1  4 }

ne843Ps1Sys OBJECT-TYPE
SYNTAX      DisplayString
MAX-ACCESS  read-write
STATUS      current
DESCRIPTION
"System Description"
 ::= { ne843Ps1  5 }

ne843Ps1Swv OBJECT-TYPE
SYNTAX      DisplayString
MAX-ACCESS  read-only
STATUS      current
DESCRIPTION
"Software Version"
 ::= { ne843Ps1  6 }

ne843Ps1Verw OBJECT-TYPE
SYNTAX      DisplayString
MAX-ACCESS  read-only
STATUS      current
DESCRIPTION
"Web Page Version"
 ::= { ne843Ps1  7 }

ne843Ps1Verb OBJECT-TYPE
SYNTAX      DisplayString
MAX-ACCESS  read-only
STATUS      current
DESCRIPTION
"Boot Block Version"
 ::= { ne843Ps1  8 }

ne843Ps1Verd OBJECT-TYPE
SYNTAX      DisplayString
MAX-ACCESS  read-only
STATUS      current
DESCRIPTION
"Display Version"
 ::= { ne843Ps1  9 }

ne843Ps1Dflt OBJECT-TYPE
SYNTAX      DisplayString
MAX-ACCESS  read-only
STATUS      current
DESCRIPTION
"Defaults Version"
 ::= { ne843Ps1  10 }

ne843Ps1Brc OBJECT-TYPE
SYNTAX      DisplayString
MAX-ACCESS  read-only
STATUS      current
DESCRIPTION
"Board Code"
 ::= { ne843Ps1  11 }

ne843Ps1Sn OBJECT-TYPE
SYNTAX      DisplayString
MAX-ACCESS  read-only
STATUS      current
DESCRIPTION
"Serial Number"
 ::= { ne843Ps1  12 }

ne843Ps1Dat OBJECT-TYPE
SYNTAX      DisplayString
MAX-ACCESS  read-write
STATUS      current
DESCRIPTION
"System Date"
 ::= { ne843Ps1  13 }

ne843Ps1Dtf OBJECT-TYPE
SYNTAX      DisplayString
MAX-ACCESS  read-write
STATUS      current
DESCRIPTION
"Date Format
Values:
mm/dd/yyyy,
dd/mm/yyyy,
yyyy/mm/dd
"
 ::= { ne843Ps1  14 }

ne843Ps1Tim OBJECT-TYPE
SYNTAX      DisplayString
MAX-ACCESS  read-write
STATUS      current
DESCRIPTION
"System Time"
 ::= { ne843Ps1  15 }

ne843Ps1Tmf OBJECT-TYPE
SYNTAX      INTEGER {
h12(12),
h24(24)
}
MAX-ACCESS  read-write
STATUS      current
DESCRIPTION
"System Time Format
Values:
h12(12),
h24(24)
"
 ::= { ne843Ps1  16 }

ne843Ps1Dls OBJECT-TYPE
SYNTAX      INTEGER {
off(0),
on(1)
}
MAX-ACCESS  read-write
STATUS      current
DESCRIPTION
"Daylight Saving
Values:
off(0),
on(1)
"
 ::= { ne843Ps1  17 }

ne843Ps1Lng OBJECT-TYPE
SYNTAX      DisplayString
MAX-ACCESS  read-write
STATUS      current
DESCRIPTION
"Front Panel Language
Values:
ENGLISH,
OTHER
"
 ::= { ne843Ps1  18 }

ne843Ps1Tun OBJECT-TYPE
SYNTAX      DisplayString
MAX-ACCESS  read-write
STATUS      current
DESCRIPTION
"Temperature Units
Values:
C,
F
"
 ::= { ne843Ps1  19 }

ne843Ps1Cem OBJECT-TYPE
SYNTAX      INTEGER {
off(0),
on(1)
}
MAX-ACCESS  read-write
STATUS      current
DESCRIPTION
"Critical Equals Major
Values:
off(0),
on(1)
"
 ::= { ne843Ps1  20 }

ne843Ps1Fpc OBJECT-TYPE
SYNTAX      INTEGER {
disable(0),
enable(1)
}
MAX-ACCESS  read-write
STATUS      current
DESCRIPTION
"Front Panel Configuration
Values:
disable(0),
enable(1)
"
 ::= { ne843Ps1  21 }

ne843Ps1Rrf OBJECT-TYPE
SYNTAX      INTEGER {
disable(0),
enable(1)
}
MAX-ACCESS  read-write
STATUS      current
DESCRIPTION
"Remote Rectifier Off
Values:
disable(0),
enable(1)
"
 ::= { ne843Ps1  22 }

ne843Ps1Poe OBJECT-TYPE
SYNTAX      INTEGER {
disable(0),
enable(1)
}
MAX-ACCESS  read-write
STATUS      current
DESCRIPTION
"Power Off Enable
Values:
disable(0),
enable(1)
"
 ::= { ne843Ps1  23 }

ne843Ps1Usl OBJECT-TYPE
SYNTAX      INTEGER {
uninstall(1)
}
MAX-ACCESS  read-write
STATUS      current
DESCRIPTION
"Uninstall Missing Equipment
Values:
uninstall(1)
"
 ::= { ne843Ps1  24 }

ne843Ps1Usr OBJECT-TYPE
SYNTAX      INTEGER {
disable(0),
enable(1)
}
MAX-ACCESS  read-write
STATUS      current
DESCRIPTION
"Enable User Accounts
Values:
disable(0),
enable(1)
"
 ::= { ne843Ps1  25 }

ne843Ps1Ptt OBJECT-TYPE
SYNTAX      DisplayString
MAX-ACCESS  read-only
STATUS      current
DESCRIPTION
"Communication Port Type
Values:
LOCAL,
MODEM
"
 ::= { ne843Ps1  26 }

ne843Ps1Amt OBJECT-TYPE
SYNTAX      Integer32
UNITS       "C"
MAX-ACCESS  read-only
STATUS      current
DESCRIPTION
"Ambient Temperature (C)"
 ::= { ne843Ps1  27 }

ne843Ps1Fst OBJECT-TYPE
SYNTAX      DisplayString
MAX-ACCESS  read-write
STATUS      current
DESCRIPTION
"Factory Defaults"
 ::= { ne843Ps1  28 }

ne843Ps1Fstl OBJECT-TYPE
SYNTAX      DisplayString
MAX-ACCESS  read-only
STATUS      current
DESCRIPTION
"Factory Defaults List"
 ::= { ne843Ps1  29 }

ne843Ps1Fpe OBJECT-TYPE
SYNTAX      INTEGER {
disable(0),
enable(1)
}
MAX-ACCESS  read-write
STATUS      current
DESCRIPTION
"Front Panel Pin Enable
Values:
disable(0),
enable(1)
"
 ::= { ne843Ps1  30 }

ne843Ps1Fpt OBJECT-TYPE
SYNTAX      Integer32
MAX-ACCESS  read-write
STATUS      current
DESCRIPTION
"Front Panel Pin Timeout"
 ::= { ne843Ps1  31 }

ne843Ps1Rss OBJECT-TYPE
SYNTAX      INTEGER {
restart(1)
}
MAX-ACCESS  read-write
STATUS      current
DESCRIPTION
"Restart Devices
Values:
restart(1)
"
 ::= { ne843Ps1  32 }

ne843Ps1Ast OBJECT-TYPE
SYNTAX      DisplayString
MAX-ACCESS  read-only
STATUS      current
DESCRIPTION
"System Alarm State"
 ::= { ne843Ps1  33 }

ne843Ps1Dss OBJECT-TYPE
SYNTAX      DisplayString
MAX-ACCESS  read-write
STATUS      current
DESCRIPTION
"Daylight Saving Start mon:wk:dow:min or, mon:-1:dom:min"
 ::= { ne843Ps1  34 }

ne843Ps1Dse OBJECT-TYPE
SYNTAX      DisplayString
MAX-ACCESS  read-write
STATUS      current
DESCRIPTION
"Daylight Saving End mon:wk:dow:min or, mon:-1:dom:min"
 ::= { ne843Ps1  35 }

ne843Ps1Epr OBJECT-TYPE
SYNTAX      DisplayString
MAX-ACCESS  read-only
STATUS      current
DESCRIPTION
"External Password Reset
Value:
Alarm report from EPR1
"
 ::= { ne843Ps1  36 }

ne843Ps1Pfd OBJECT-TYPE
SYNTAX      DisplayString
MAX-ACCESS  read-only
STATUS      current
DESCRIPTION
"Passwords At Default
Value:
Alarm report from PFD1
"
 ::= { ne843Ps1  37 }

ne843Ps1Exl OBJECT-TYPE
SYNTAX      DisplayString
MAX-ACCESS  read-only
STATUS      current
DESCRIPTION
"Excessive Login Attempts
Value:
Alarm report from EXL1
"
 ::= { ne843Ps1  38 }

ne843Ps1Bbl OBJECT-TYPE
SYNTAX      DisplayString
MAX-ACCESS  read-only
STATUS      current
DESCRIPTION
"Memory Backup Battery Low
Value:
Alarm report from BBL1
"
 ::= { ne843Ps1  39 }

ne843Ps1Clc OBJECT-TYPE
SYNTAX      DisplayString
MAX-ACCESS  read-only
STATUS      current
DESCRIPTION
"Clock Changed
Value:
Alarm report from CLC1
"
 ::= { ne843Ps1  40 }

ne843Ps1Stf OBJECT-TYPE
SYNTAX      DisplayString
MAX-ACCESS  read-only
STATUS      current
DESCRIPTION
"Self Test Failed
Value:
Alarm report from STF1
"
 ::= { ne843Ps1  41 }

ne843Ps1Pgi OBJECT-TYPE
SYNTAX      DisplayString
MAX-ACCESS  read-only
STATUS      current
DESCRIPTION
"Program Line Invalid
Value:
Alarm report from PGI1
"
 ::= { ne843Ps1  42 }

ne843Ps1Cch OBJECT-TYPE
SYNTAX      DisplayString
MAX-ACCESS  read-only
STATUS      current
DESCRIPTION
"Configuration Changed
Value:
Alarm report from CCH1
"
 ::= { ne843Ps1  43 }

ne843Ps1Hcl OBJECT-TYPE
SYNTAX      DisplayString
MAX-ACCESS  read-only
STATUS      current
DESCRIPTION
"History Cleared
Value:
Alarm report from HCL1
"
 ::= { ne843Ps1  44 }

ne843Ps1Ax1 OBJECT-TYPE
SYNTAX      DisplayString
MAX-ACCESS  read-only
STATUS      current
DESCRIPTION
"Auxiliary Event 1
Value:
Alarm report from AUX1
"
 ::= { ne843Ps1  45 }

ne843Ps1Ax2 OBJECT-TYPE
SYNTAX      DisplayString
MAX-ACCESS  read-only
STATUS      current
DESCRIPTION
"Auxiliary Event 2
Value:
Alarm report from AUX2
"
 ::= { ne843Ps1  46 }

ne843Ps1Ax3 OBJECT-TYPE
SYNTAX      DisplayString
MAX-ACCESS  read-only
STATUS      current
DESCRIPTION
"Auxiliary Event 3
Value:
Alarm report from AUX3
"
 ::= { ne843Ps1  47 }

ne843Ps1Ax4 OBJECT-TYPE
SYNTAX      DisplayString
MAX-ACCESS  read-only
STATUS      current
DESCRIPTION
"Auxiliary Event 4
Value:
Alarm report from AUX4
"
 ::= { ne843Ps1  48 }

ne843Ps1Ax5 OBJECT-TYPE
SYNTAX      DisplayString
MAX-ACCESS  read-only
STATUS      current
DESCRIPTION
"Auxiliary Event 5
Value:
Alarm report from AUX5
"
 ::= { ne843Ps1  49 }

ne843Ps1Ax6 OBJECT-TYPE
SYNTAX      DisplayString
MAX-ACCESS  read-only
STATUS      current
DESCRIPTION
"Auxiliary Event 6
Value:
Alarm report from AUX6
"
 ::= { ne843Ps1  50 }

ne843Ps1Fan24 OBJECT-TYPE
SYNTAX      DisplayString
MAX-ACCESS  read-only
STATUS      current
DESCRIPTION
"24 V Fuse Minor
Value:
Alarm report from FAN1
"
 ::= { ne843Ps1  51 }

ne843Ps1Fan48 OBJECT-TYPE
SYNTAX      DisplayString
MAX-ACCESS  read-only
STATUS      current
DESCRIPTION
"48 V Fuse Minor
Value:
Alarm report from FAN2
"
 ::= { ne843Ps1  52 }

ne843Ps1Faj24 OBJECT-TYPE
SYNTAX      DisplayString
MAX-ACCESS  read-only
STATUS      current
DESCRIPTION
"24 V Fuse Major
Value:
Alarm report from FAJ1
"
 ::= { ne843Ps1  53 }

ne843Ps1Faj48 OBJECT-TYPE
SYNTAX      DisplayString
MAX-ACCESS  read-only
STATUS      current
DESCRIPTION
"48 V Fuse Major
Value:
Alarm report from FAJ2
"
 ::= { ne843Ps1  54 }

ne843Ps1Accl OBJECT-TYPE
SYNTAX      DisplayString
MAX-ACCESS  read-only
STATUS      current
DESCRIPTION
"Relay List"
 ::= { ne843Ps1  55 }

ne843Ps1Ledl OBJECT-TYPE
SYNTAX      DisplayString
MAX-ACCESS  read-only
STATUS      current
DESCRIPTION
"LED List"
 ::= { ne843Ps1  56 }

ne843Ps1Ax7 OBJECT-TYPE
SYNTAX      DisplayString
MAX-ACCESS  read-only
STATUS      current
DESCRIPTION
"Auxiliary Event 7
Value:
Alarm report from AUX7
"
 ::= { ne843Ps1  57 }

ne843Ps1Ax8 OBJECT-TYPE
SYNTAX      DisplayString
MAX-ACCESS  read-only
STATUS      current
DESCRIPTION
"Auxiliary Event 8
Value:
Alarm report from AUX8
"
 ::= { ne843Ps1  58 }

ne843Ps1Ax9 OBJECT-TYPE
SYNTAX      DisplayString
MAX-ACCESS  read-only
STATUS      current
DESCRIPTION
"Auxiliary Event 9
Value:
Alarm report from AUX9
"
 ::= { ne843Ps1  59 }

ne843Ps1Ax10 OBJECT-TYPE
SYNTAX      DisplayString
MAX-ACCESS  read-only
STATUS      current
DESCRIPTION
"Auxiliary Event 10
Value:
Alarm report from AUX10
"
 ::= { ne843Ps1  60 }

ne843Ps1Ax11 OBJECT-TYPE
SYNTAX      DisplayString
MAX-ACCESS  read-only
STATUS      current
DESCRIPTION
"Auxiliary Event 11
Value:
Alarm report from AUX11
"
 ::= { ne843Ps1  61 }

ne843Ps1Ax12 OBJECT-TYPE
SYNTAX      DisplayString
MAX-ACCESS  read-only
STATUS      current
DESCRIPTION
"Auxiliary Event 12
Value:
Alarm report from AUX12
"
 ::= { ne843Ps1  62 }

ne843Ps1Cid OBJECT-TYPE
SYNTAX      INTEGER {
disable(0),
enable(1)
}
MAX-ACCESS  read-write
STATUS      current
DESCRIPTION
"Controller Assignes IDs
Values:
disable(0),
enable(1)
"
 ::= { ne843Ps1  63 }

ne843Ps1Lngl OBJECT-TYPE
SYNTAX      DisplayString
MAX-ACCESS  read-only
STATUS      current
DESCRIPTION
"Available Languages"
 ::= { ne843Ps1  64 }

ne843Ps1Amtl OBJECT-TYPE
SYNTAX      DisplayString
MAX-ACCESS  read-only
STATUS      current
DESCRIPTION
"Low Ambient Temperature
Value:
Alarm report from AMTL1
"
 ::= { ne843Ps1  65 }

ne843Ps1Amth OBJECT-TYPE
SYNTAX      DisplayString
MAX-ACCESS  read-only
STATUS      current
DESCRIPTION
"High Ambient Temperature
Value:
Alarm report from AMTH1
"
 ::= { ne843Ps1  66 }

ne843Ps1Cc OBJECT-TYPE
SYNTAX      DisplayString
MAX-ACCESS  read-only
STATUS      current
DESCRIPTION
"Comcode"
 ::= { ne843Ps1  67 }

ne843Ps1Clei OBJECT-TYPE
SYNTAX      DisplayString
MAX-ACCESS  read-only
STATUS      current
DESCRIPTION
"CLEI Code"
 ::= { ne843Ps1  68 }

ne843Ps1Ser OBJECT-TYPE
SYNTAX      DisplayString
MAX-ACCESS  read-only
STATUS      current
DESCRIPTION
"Series"
 ::= { ne843Ps1  69 }

ne843Ps1Lamt OBJECT-TYPE
SYNTAX      Integer32
UNITS       "C"
MAX-ACCESS  read-only
STATUS      current
DESCRIPTION
"Lowest Ambient Temperature (C)"
 ::= { ne843Ps1  70 }

ne843Ps1Nat OBJECT-TYPE
SYNTAX      Integer32
MAX-ACCESS  read-only
STATUS      current
DESCRIPTION
"Number of Ambient Temperature Probes Present"
 ::= { ne843Ps1  71 }

ne843Ps1Blr OBJECT-TYPE
SYNTAX      DisplayString
MAX-ACCESS  read-write
STATUS      current
DESCRIPTION
"Bay Lamp Relay
Values:
,
R1,
R2,
R3,
R4,
R5,
R6,
R7
"
 ::= { ne843Ps1  72 }

ne843Ps1Tzo OBJECT-TYPE
SYNTAX      Integer32
UNITS       "Minutes"
MAX-ACCESS  read-write
STATUS      current
DESCRIPTION
"Timezone Offset (Minutes)"
 ::= { ne843Ps1  73 }

ne843Ps1Crt OBJECT-TYPE
SYNTAX      DisplayString
MAX-ACCESS  read-only
STATUS      current
DESCRIPTION
"Configuration Changed Reboot Required
Value:
Alarm report from CRT1
"
 ::= { ne843Ps1  74 }

ne843Ps1Nhat OBJECT-TYPE
SYNTAX      Integer32
UNITS       "C"
MAX-ACCESS  read-write
STATUS      current
DESCRIPTION
"Next Highest Ambient Temperature (C)"
 ::= { ne843Ps1  75 }

ne843Ps1Nal OBJECT-TYPE
SYNTAX      Integer32
MAX-ACCESS  read-only
STATUS      current
DESCRIPTION
"Number of Total Alarms Active"
 ::= { ne843Ps1  76 }

ne843Ps1Ncr OBJECT-TYPE
SYNTAX      Integer32
MAX-ACCESS  read-only
STATUS      current
DESCRIPTION
"Number of Total Critical Alarms Active"
 ::= { ne843Ps1  77 }

ne843Ps1Nmj OBJECT-TYPE
SYNTAX      Integer32
MAX-ACCESS  read-only
STATUS      current
DESCRIPTION
"Number of Total Major Alarms Active"
 ::= { ne843Ps1  78 }

ne843Ps1Nmn OBJECT-TYPE
SYNTAX      Integer32
MAX-ACCESS  read-only
STATUS      current
DESCRIPTION
"Number of Total Minor Alarms Active"
 ::= { ne843Ps1  79 }

ne843Ps1Nwa OBJECT-TYPE
SYNTAX      Integer32
MAX-ACCESS  read-only
STATUS      current
DESCRIPTION
"Number of Total Warnings Active"
 ::= { ne843Ps1  80 }

ne843Ps1Nre OBJECT-TYPE
SYNTAX      Integer32
MAX-ACCESS  read-only
STATUS      current
DESCRIPTION
"Number of Total Record Only Events Active"
 ::= { ne843Ps1  81 }

ne843Ps1Ere OBJECT-TYPE
SYNTAX      INTEGER {
disable(0),
enable(1)
}
MAX-ACCESS  read-write
STATUS      current
DESCRIPTION
"PCR/PMJ/PMN Enahnced Relays Enabled
Values:
disable(0),
enable(1)
"
 ::= { ne843Ps1  82 }


--
-- object ne843At1
--

ne843At1 OBJECT IDENTIFIER  ::= { ne843  3 }

ne843At1Ide OBJECT-TYPE
SYNTAX      DisplayString
MAX-ACCESS  read-only
STATUS      current
DESCRIPTION
"Identifier"
 ::= { ne843At1  1 }

ne843At1Des OBJECT-TYPE
SYNTAX      DisplayString
MAX-ACCESS  read-write
STATUS      current
DESCRIPTION
"Description"
 ::= { ne843At1  2 }

ne843At1Stt OBJECT-TYPE
SYNTAX      INTEGER {
inactive(0),
active(1)
}
MAX-ACCESS  read-write
STATUS      current
DESCRIPTION
"Alarm Test Active
Values:
inactive(0),
active(1)
"
 ::= { ne843At1  3 }

ne843At1Stg OBJECT-TYPE
SYNTAX      DisplayString
MAX-ACCESS  read-only
STATUS      current
DESCRIPTION
"Stage"
 ::= { ne843At1  4 }

ne843At1Lte OBJECT-TYPE
SYNTAX      INTEGER {
disable(0),
enable(1)
}
MAX-ACCESS  read-write
STATUS      current
DESCRIPTION
"Alarm Test Enable
Values:
disable(0),
enable(1)
"
 ::= { ne843At1  5 }

ne843At1Dur OBJECT-TYPE
SYNTAX      Integer32(5..300)
UNITS       "Seconds"
MAX-ACCESS  read-write
STATUS      current
DESCRIPTION
"Alarm Contact Duration (Seconds)"
 ::= { ne843At1  6 }

ne843At1Pcr OBJECT-TYPE
SYNTAX      INTEGER {
no(0),
yes(1)
}
MAX-ACCESS  read-write
STATUS      current
DESCRIPTION
"Power Critical
Values:
no(0),
yes(1)
"
 ::= { ne843At1  7 }

ne843At1Pmj OBJECT-TYPE
SYNTAX      INTEGER {
no(0),
yes(1)
}
MAX-ACCESS  read-write
STATUS      current
DESCRIPTION
"Power Major
Values:
no(0),
yes(1)
"
 ::= { ne843At1  8 }

ne843At1Pmn OBJECT-TYPE
SYNTAX      INTEGER {
no(0),
yes(1)
}
MAX-ACCESS  read-write
STATUS      current
DESCRIPTION
"Power Minor
Values:
no(0),
yes(1)
"
 ::= { ne843At1  9 }

ne843At1R1 OBJECT-TYPE
SYNTAX      INTEGER {
no(0),
yes(1)
}
MAX-ACCESS  read-write
STATUS      current
DESCRIPTION
"Test Relay 1
Values:
no(0),
yes(1)
"
 ::= { ne843At1  10 }

ne843At1R2 OBJECT-TYPE
SYNTAX      INTEGER {
no(0),
yes(1)
}
MAX-ACCESS  read-write
STATUS      current
DESCRIPTION
"Test Relay 2
Values:
no(0),
yes(1)
"
 ::= { ne843At1  11 }

ne843At1R3 OBJECT-TYPE
SYNTAX      INTEGER {
no(0),
yes(1)
}
MAX-ACCESS  read-write
STATUS      current
DESCRIPTION
"Test Relay 3
Values:
no(0),
yes(1)
"
 ::= { ne843At1  12 }

ne843At1R4 OBJECT-TYPE
SYNTAX      INTEGER {
no(0),
yes(1)
}
MAX-ACCESS  read-write
STATUS      current
DESCRIPTION
"Test Relay 4
Values:
no(0),
yes(1)
"
 ::= { ne843At1  13 }

ne843At1R5 OBJECT-TYPE
SYNTAX      INTEGER {
no(0),
yes(1)
}
MAX-ACCESS  read-write
STATUS      current
DESCRIPTION
"Test Relay 5
Values:
no(0),
yes(1)
"
 ::= { ne843At1  14 }

ne843At1R6 OBJECT-TYPE
SYNTAX      INTEGER {
no(0),
yes(1)
}
MAX-ACCESS  read-write
STATUS      current
DESCRIPTION
"Test Relay 6
Values:
no(0),
yes(1)
"
 ::= { ne843At1  15 }

ne843At1R7 OBJECT-TYPE
SYNTAX      INTEGER {
no(0),
yes(1)
}
MAX-ACCESS  read-write
STATUS      current
DESCRIPTION
"Test Relay 7
Values:
no(0),
yes(1)
"
 ::= { ne843At1  16 }

ne843At1Ets OBJECT-TYPE
SYNTAX      INTEGER {
inactive(0),
active(1)
}
MAX-ACCESS  read-write
STATUS      current
DESCRIPTION
"Do Email Test
Values:
inactive(0),
active(1)
"
 ::= { ne843At1  17 }

ne843At1Ems OBJECT-TYPE
SYNTAX      DisplayString
MAX-ACCESS  read-only
STATUS      current
DESCRIPTION
"Email Test Results"
 ::= { ne843At1  18 }

ne843At1Bzi OBJECT-TYPE
SYNTAX      Integer32(5..300)
UNITS       "Seconds"
MAX-ACCESS  read-write
STATUS      current
DESCRIPTION
"Audio Test Duration (Seconds)"
 ::= { ne843At1  19 }

ne843At1Bzt OBJECT-TYPE
SYNTAX      DisplayString
MAX-ACCESS  read-write
STATUS      current
DESCRIPTION
"Audio Test Active
Values:
,
LOCAL
"
 ::= { ne843At1  20 }

ne843At1Irt OBJECT-TYPE
SYNTAX      DisplayString
MAX-ACCESS  read-write
STATUS      current
DESCRIPTION
"Individual Relay Test State
Values:
,
PCR,
PMJ,
PMN,
R1,
R2,
R3,
R4,
R5,
R6,
R7
"
 ::= { ne843At1  21 }

ne843At1Ata OBJECT-TYPE
SYNTAX      DisplayString
MAX-ACCESS  read-only
STATUS      current
DESCRIPTION
"Alarm Test Active
Value:
Alarm report from ATA1
"
 ::= { ne843At1  22 }

ne843At1Atb OBJECT-TYPE
SYNTAX      DisplayString
MAX-ACCESS  read-only
STATUS      current
DESCRIPTION
"Alarm Test Aborted
Value:
Alarm report from ATB1
"
 ::= { ne843At1  23 }

ne843At1Snt OBJECT-TYPE
SYNTAX      INTEGER {
start(1)
}
MAX-ACCESS  read-write
STATUS      current
DESCRIPTION
"Email Test
Values:
start(1)
"
 ::= { ne843At1  24 }


--
-- table TRS
--

ne843TrsTable    OBJECT-TYPE
SYNTAX SEQUENCE OF Ne843TrsEntry
MAX-ACCESS not-accessible
STATUS current
DESCRIPTION
        "Table of all Trend data"
 ::= { ne843  4 }

ne843TrsEntry OBJECT-TYPE
SYNTAX     Ne843TrsEntry
MAX-ACCESS  not-accessible
STATUS      current
DESCRIPTION
       "Entry of information for one Trend"
INDEX { ne843TrsEntryIndex }
 ::= { ne843TrsTable  1 }

Ne843TrsEntry ::= SEQUENCE {
ne843TrsEntryIndex   INTEGER,
ne843TrsEntryIde   DisplayString,
ne843TrsEntryDes   DisplayString,
ne843TrsEntrySrc   DisplayString
}

ne843TrsEntryIndex OBJECT-TYPE
SYNTAX      INTEGER (0..2147483647)
MAX-ACCESS  read-only
STATUS      current
DESCRIPTION
"Table Index"
 ::= { ne843TrsEntry  1 }

ne843TrsEntryIde OBJECT-TYPE
SYNTAX      DisplayString
MAX-ACCESS  read-only
STATUS      current
DESCRIPTION
"Identifier"
 ::= { ne843TrsEntry  2 }

ne843TrsEntryDes OBJECT-TYPE
SYNTAX      DisplayString
MAX-ACCESS  read-write
STATUS      current
DESCRIPTION
"Description"
 ::= { ne843TrsEntry  3 }

ne843TrsEntrySrc OBJECT-TYPE
SYNTAX      DisplayString
MAX-ACCESS  read-write
STATUS      current
DESCRIPTION
"Source"
 ::= { ne843TrsEntry  4 }



--
-- object ne843Aco1
--

ne843Aco1 OBJECT IDENTIFIER  ::= { ne843  5 }

ne843Aco1Ide OBJECT-TYPE
SYNTAX      DisplayString
MAX-ACCESS  read-only
STATUS      current
DESCRIPTION
"Identifier"
 ::= { ne843Aco1  1 }

ne843Aco1Des OBJECT-TYPE
SYNTAX      DisplayString
MAX-ACCESS  read-write
STATUS      current
DESCRIPTION
"Description"
 ::= { ne843Aco1  2 }

ne843Aco1Stt OBJECT-TYPE
SYNTAX      INTEGER {
inactive(0),
active(1)
}
MAX-ACCESS  read-write
STATUS      current
DESCRIPTION
"Alarm Cut-off State
Values:
inactive(0),
active(1)
"
 ::= { ne843Aco1  3 }

ne843Aco1Cst OBJECT-TYPE
SYNTAX      INTEGER {
inactive(0),
active(1)
}
MAX-ACCESS  read-only
STATUS      current
DESCRIPTION
"Critical Alarm Cut-off State
Values:
inactive(0),
active(1)
"
 ::= { ne843Aco1  4 }

ne843Aco1Cae OBJECT-TYPE
SYNTAX      INTEGER {
disable(0),
enable(1)
}
MAX-ACCESS  read-write
STATUS      current
DESCRIPTION
"Critical Alarm Cut-off Enable
Values:
disable(0),
enable(1)
"
 ::= { ne843Aco1  5 }

ne843Aco1Cto OBJECT-TYPE
SYNTAX      Integer32(1..8)
UNITS       "Hours"
MAX-ACCESS  read-write
STATUS      current
DESCRIPTION
"Critical Alarm Cut-off Timeout (Hours)"
 ::= { ne843Aco1  6 }

ne843Aco1Jst OBJECT-TYPE
SYNTAX      INTEGER {
inactive(0),
active(1)
}
MAX-ACCESS  read-only
STATUS      current
DESCRIPTION
"Major Alarm Cut-off State
Values:
inactive(0),
active(1)
"
 ::= { ne843Aco1  7 }

ne843Aco1Jae OBJECT-TYPE
SYNTAX      INTEGER {
disable(0),
enable(1)
}
MAX-ACCESS  read-write
STATUS      current
DESCRIPTION
"Major Alarm Cut-off Enable
Values:
disable(0),
enable(1)
"
 ::= { ne843Aco1  8 }

ne843Aco1Jto OBJECT-TYPE
SYNTAX      Integer32(1..8)
UNITS       "Hours"
MAX-ACCESS  read-write
STATUS      current
DESCRIPTION
"Major Alarm Cut-off Timeout (Hours)"
 ::= { ne843Aco1  9 }

ne843Aco1Nst OBJECT-TYPE
SYNTAX      INTEGER {
inactive(0),
active(1)
}
MAX-ACCESS  read-only
STATUS      current
DESCRIPTION
"Minor Alarm Cut-off State
Values:
inactive(0),
active(1)
"
 ::= { ne843Aco1  10 }

ne843Aco1Nae OBJECT-TYPE
SYNTAX      INTEGER {
disable(0),
enable(1)
}
MAX-ACCESS  read-write
STATUS      current
DESCRIPTION
"Minor Alarm Cut-off Enable
Values:
disable(0),
enable(1)
"
 ::= { ne843Aco1  11 }

ne843Aco1Nto OBJECT-TYPE
SYNTAX      Integer32(1..72)
UNITS       "Hours"
MAX-ACCESS  read-write
STATUS      current
DESCRIPTION
"Minor Alarm Cut-off Timeout (Hours)"
 ::= { ne843Aco1  12 }

ne843Aco1Lbe OBJECT-TYPE
SYNTAX      INTEGER {
disable(0),
enable(1)
}
MAX-ACCESS  read-write
STATUS      current
DESCRIPTION
"Local Buzzer Enable
Values:
disable(0),
enable(1)
"
 ::= { ne843Aco1  13 }

ne843Aco1Aac OBJECT-TYPE
SYNTAX      DisplayString
MAX-ACCESS  read-only
STATUS      current
DESCRIPTION
"ACO Active
Value:
Alarm report from AAC1
"
 ::= { ne843Aco1  14 }


--
-- object ne843Gm1
--

ne843Gm1 OBJECT IDENTIFIER  ::= { ne843  6 }

ne843Gm1Ide OBJECT-TYPE
SYNTAX      DisplayString
MAX-ACCESS  read-only
STATUS      current
DESCRIPTION
"Identifier"
 ::= { ne843Gm1  1 }

ne843Gm1Des OBJECT-TYPE
SYNTAX      DisplayString
MAX-ACCESS  read-write
STATUS      current
DESCRIPTION
"Description"
 ::= { ne843Gm1  2 }

ne843Gm1Lse OBJECT-TYPE
SYNTAX      INTEGER {
disable(0),
enable(1)
}
MAX-ACCESS  read-write
STATUS      current
DESCRIPTION
"Load Share Enable
Values:
disable(0),
enable(1)
"
 ::= { ne843Gm1  3 }

ne843Gm1Rme OBJECT-TYPE
SYNTAX      INTEGER {
disable(0),
enable(1)
}
MAX-ACCESS  read-write
STATUS      current
DESCRIPTION
"Redundancy Monitor
Values:
disable(0),
enable(1)
"
 ::= { ne843Gm1  4 }

ne843Gm1Fsd OBJECT-TYPE
SYNTAX      Integer32(25000..30000|50000..60000)
UNITS       "mV"
MAX-ACCESS  read-write
STATUS      current
DESCRIPTION
"Float High Voltage Shutdown (mV)"
 ::= { ne843Gm1  5 }

ne843Gm1Bsd OBJECT-TYPE
SYNTAX      Integer32(26000..30000|52000..60000)
UNITS       "mV"
MAX-ACCESS  read-write
STATUS      current
DESCRIPTION
"Boost High Voltage Shutdown (mV)"
 ::= { ne843Gm1  6 }

ne843Gm1Fsp OBJECT-TYPE
SYNTAX      Integer32(22000..28000|44000..56500)
UNITS       "mV"
MAX-ACCESS  read-write
STATUS      current
DESCRIPTION
"Float Set Point (mV)"
 ::= { ne843Gm1  7 }

ne843Gm1Bsp OBJECT-TYPE
SYNTAX      Integer32(22000..30000|48000..60000)
UNITS       "mV"
MAX-ACCESS  read-write
STATUS      current
DESCRIPTION
"Boost Set Point (mV)"
 ::= { ne843Gm1  8 }

ne843Gm1Fcl OBJECT-TYPE
SYNTAX      Integer32(30..110)
UNITS       "%"
MAX-ACCESS  read-write
STATUS      current
DESCRIPTION
"Float Current Limit (%)"
 ::= { ne843Gm1  9 }

ne843Gm1Bcl OBJECT-TYPE
SYNTAX      Integer32(30..110)
UNITS       "%"
MAX-ACCESS  read-write
STATUS      current
DESCRIPTION
"Boost Current Limit (%)"
 ::= { ne843Gm1  10 }

ne843Gm1Oft OBJECT-TYPE
SYNTAX      INTEGER {
start(1)
}
MAX-ACCESS  read-write
STATUS      current
DESCRIPTION
"Or-ing FET Test
Values:
start(1)
"
 ::= { ne843Gm1  11 }

ne843Gm1Wie OBJECT-TYPE
SYNTAX      INTEGER {
disable(0),
enable(1)
}
MAX-ACCESS  read-write
STATUS      current
DESCRIPTION
"Walk-in Enable
Values:
disable(0),
enable(1)
"
 ::= { ne843Gm1  12 }

ne843Gm1Sof OBJECT-TYPE
SYNTAX      INTEGER {
disable(0),
enable(1)
}
MAX-ACCESS  read-write
STATUS      current
DESCRIPTION
"Shorted ORing FET Test Enable
Values:
disable(0),
enable(1)
"
 ::= { ne843Gm1  13 }

ne843Gm1Lsfe OBJECT-TYPE
SYNTAX      INTEGER {
disable(0),
enable(1)
}
MAX-ACCESS  read-write
STATUS      current
DESCRIPTION
"Load Share Fail Enable
Values:
disable(0),
enable(1)
"
 ::= { ne843Gm1  14 }

ne843Gm1Nro OBJECT-TYPE
SYNTAX      DisplayString
MAX-ACCESS  read-only
STATUS      current
DESCRIPTION
"Number of Rectifiers On"
 ::= { ne843Gm1  15 }

ne843Gm1Lst OBJECT-TYPE
SYNTAX      Integer32
MAX-ACCESS  read-only
STATUS      current
DESCRIPTION
"Load Share Target"
 ::= { ne843Gm1  16 }

ne843Gm1Nro1 OBJECT-TYPE
SYNTAX      Integer32
MAX-ACCESS  read-only
STATUS      current
DESCRIPTION
"Number of Rectifiers On"
 ::= { ne843Gm1  17 }


--
-- table REC
--

ne843RecTable    OBJECT-TYPE
SYNTAX SEQUENCE OF Ne843RecEntry
MAX-ACCESS not-accessible
STATUS current
DESCRIPTION
        "Table of all Rectifier data"
 ::= { ne843  7 }

ne843RecEntry OBJECT-TYPE
SYNTAX     Ne843RecEntry
MAX-ACCESS  not-accessible
STATUS      current
DESCRIPTION
       "Entry of information for one Rectifier"
INDEX { ne843RecEntryIndex }
 ::= { ne843RecTable  1 }

Ne843RecEntry ::= SEQUENCE {
ne843RecEntryIndex   INTEGER,
ne843RecEntryIde   DisplayString,
ne843RecEntryDes   DisplayString,
ne843RecEntryTyp   DisplayString,
ne843RecEntrySn   DisplayString,
ne843RecEntryAdc   Integer32,
ne843RecEntryVdc   Integer32,
ne843RecEntryStt   DisplayString,
ne843RecEntryCap   Integer32,
ne843RecEntryVac   Integer32,
ne843RecEntryAac   Integer32,
ne843RecEntryTmp   Integer32,
ne843RecEntrySeq   INTEGER,
ne843RecEntryRfa   DisplayString,
ne843RecEntryAcf   DisplayString,
ne843RecEntryMan   DisplayString,
ne843RecEntryDid   DisplayString,
ne843RecEntryClm   DisplayString,
ne843RecEntryRcf   DisplayString,
ne843RecEntryRfn   DisplayString,
ne843RecEntryRif   DisplayString,
ne843RecEntryLsf   DisplayString,
ne843RecEntryCc   DisplayString,
ne843RecEntryClei   DisplayString,
ne843RecEntrySer   DisplayString,
ne843RecEntryVerp   DisplayString,
ne843RecEntryVers   DisplayString,
ne843RecEntryLin   DisplayString,
ne843RecEntryHin   DisplayString,
ne843RecEntryBof   DisplayString,
ne843RecEntrySof   DisplayString,
ne843RecEntryDer   DisplayString,
ne843RecEntryEcap   Integer32,
ne843RecEntryEmod   Integer32,
ne843RecEntryMppt   Integer32,
ne843RecEntryRtm   Integer32,
ne843RecEntryVan   Integer32,
ne843RecEntryVac1   Integer32,
ne843RecEntryAac1   Integer32,
ne843RecEntryVac2   Integer32,
ne843RecEntryAac2   Integer32,
ne843RecEntryVac3   Integer32,
ne843RecEntryAac3   Integer32,
ne843RecEntryRfa1   INTEGER,
ne843RecEntryAcf1   INTEGER,
ne843RecEntryMan1   INTEGER,
ne843RecEntryDid1   INTEGER,
ne843RecEntryClm1   INTEGER,
ne843RecEntryRcf1   INTEGER,
ne843RecEntryRfn1   INTEGER,
ne843RecEntryRif1   INTEGER,
ne843RecEntryLsf1   INTEGER,
ne843RecEntryLin1   INTEGER,
ne843RecEntryHin1   INTEGER,
ne843RecEntryBof1   INTEGER,
ne843RecEntrySof1   INTEGER,
ne843RecEntryDer1   INTEGER
}

ne843RecEntryIndex OBJECT-TYPE
SYNTAX      INTEGER (0..2147483647)
MAX-ACCESS  read-only
STATUS      current
DESCRIPTION
"Table Index"
 ::= { ne843RecEntry  1 }

ne843RecEntryIde OBJECT-TYPE
SYNTAX      DisplayString
MAX-ACCESS  read-only
STATUS      current
DESCRIPTION
"Identifier"
 ::= { ne843RecEntry  2 }

ne843RecEntryDes OBJECT-TYPE
SYNTAX      DisplayString
MAX-ACCESS  read-write
STATUS      current
DESCRIPTION
"Description"
 ::= { ne843RecEntry  3 }

ne843RecEntryTyp OBJECT-TYPE
SYNTAX      DisplayString
MAX-ACCESS  read-write
STATUS      current
DESCRIPTION
"Type"
 ::= { ne843RecEntry  4 }

ne843RecEntrySn OBJECT-TYPE
SYNTAX      DisplayString
MAX-ACCESS  read-only
STATUS      current
DESCRIPTION
"Serial Number"
 ::= { ne843RecEntry  5 }

ne843RecEntryAdc OBJECT-TYPE
SYNTAX      Integer32
UNITS       "Amps"
MAX-ACCESS  read-only
STATUS      current
DESCRIPTION
"DC Current (Amps)"
 ::= { ne843RecEntry  6 }

ne843RecEntryVdc OBJECT-TYPE
SYNTAX      Integer32
UNITS       "mV"
MAX-ACCESS  read-only
STATUS      current
DESCRIPTION
"DC Voltage (mV)"
 ::= { ne843RecEntry  7 }

ne843RecEntryStt OBJECT-TYPE
SYNTAX      DisplayString
MAX-ACCESS  read-write
STATUS      current
DESCRIPTION
"State
Values:
ON,
OFF,
STANDBY,
VACANT
"
 ::= { ne843RecEntry  8 }

ne843RecEntryCap OBJECT-TYPE
SYNTAX      Integer32
UNITS       "Amps"
MAX-ACCESS  read-only
STATUS      current
DESCRIPTION
"Capacity (Amps)"
 ::= { ne843RecEntry  9 }

ne843RecEntryVac OBJECT-TYPE
SYNTAX      Integer32
UNITS       "Volts"
MAX-ACCESS  read-only
STATUS      current
DESCRIPTION
"AC Voltage (Volts)"
 ::= { ne843RecEntry  10 }

ne843RecEntryAac OBJECT-TYPE
SYNTAX      Integer32
UNITS       "mA"
MAX-ACCESS  read-only
STATUS      current
DESCRIPTION
"AC Current (mA)"
 ::= { ne843RecEntry  11 }

ne843RecEntryTmp OBJECT-TYPE
SYNTAX      Integer32
UNITS       "C"
MAX-ACCESS  read-only
STATUS      current
DESCRIPTION
"Temperature (C)"
 ::= { ne843RecEntry  12 }

ne843RecEntrySeq OBJECT-TYPE
SYNTAX      INTEGER {
no(0),
yes(1)
}
MAX-ACCESS  read-write
STATUS      current
DESCRIPTION
"Use in Sequence Enable
Values:
no(0),
yes(1)
"
 ::= { ne843RecEntry  13 }

ne843RecEntryRfa OBJECT-TYPE
SYNTAX      DisplayString
MAX-ACCESS  read-only
STATUS      current
DESCRIPTION
"Rectifier Fail"
 ::= { ne843RecEntry  14 }

ne843RecEntryAcf OBJECT-TYPE
SYNTAX      DisplayString
MAX-ACCESS  read-only
STATUS      current
DESCRIPTION
"AC Fail"
 ::= { ne843RecEntry  15 }

ne843RecEntryMan OBJECT-TYPE
SYNTAX      DisplayString
MAX-ACCESS  read-only
STATUS      current
DESCRIPTION
"Standby or Manual Off"
 ::= { ne843RecEntry  16 }

ne843RecEntryDid OBJECT-TYPE
SYNTAX      DisplayString
MAX-ACCESS  read-only
STATUS      current
DESCRIPTION
"ID Conflict"
 ::= { ne843RecEntry  17 }

ne843RecEntryClm OBJECT-TYPE
SYNTAX      DisplayString
MAX-ACCESS  read-only
STATUS      current
DESCRIPTION
"Current Limit"
 ::= { ne843RecEntry  18 }

ne843RecEntryRcf OBJECT-TYPE
SYNTAX      DisplayString
MAX-ACCESS  read-only
STATUS      current
DESCRIPTION
"Communication Failure"
 ::= { ne843RecEntry  19 }

ne843RecEntryRfn OBJECT-TYPE
SYNTAX      DisplayString
MAX-ACCESS  read-only
STATUS      current
DESCRIPTION
"Fan Failure"
 ::= { ne843RecEntry  20 }

ne843RecEntryRif OBJECT-TYPE
SYNTAX      DisplayString
MAX-ACCESS  read-only
STATUS      current
DESCRIPTION
"Internal Fault"
 ::= { ne843RecEntry  21 }

ne843RecEntryLsf OBJECT-TYPE
SYNTAX      DisplayString
MAX-ACCESS  read-only
STATUS      current
DESCRIPTION
"Loadshare Failure"
 ::= { ne843RecEntry  22 }

ne843RecEntryCc OBJECT-TYPE
SYNTAX      DisplayString
MAX-ACCESS  read-only
STATUS      current
DESCRIPTION
"Comcode"
 ::= { ne843RecEntry  23 }

ne843RecEntryClei OBJECT-TYPE
SYNTAX      DisplayString
MAX-ACCESS  read-only
STATUS      current
DESCRIPTION
"CLEI Code"
 ::= { ne843RecEntry  24 }

ne843RecEntrySer OBJECT-TYPE
SYNTAX      DisplayString
MAX-ACCESS  read-only
STATUS      current
DESCRIPTION
"Series"
 ::= { ne843RecEntry  25 }

ne843RecEntryVerp OBJECT-TYPE
SYNTAX      DisplayString
MAX-ACCESS  read-only
STATUS      current
DESCRIPTION
"Primary Software Version"
 ::= { ne843RecEntry  26 }

ne843RecEntryVers OBJECT-TYPE
SYNTAX      DisplayString
MAX-ACCESS  read-only
STATUS      current
DESCRIPTION
"Secondary Software Version"
 ::= { ne843RecEntry  27 }

ne843RecEntryLin OBJECT-TYPE
SYNTAX      DisplayString
MAX-ACCESS  read-only
STATUS      current
DESCRIPTION
"Low Input"
 ::= { ne843RecEntry  28 }

ne843RecEntryHin OBJECT-TYPE
SYNTAX      DisplayString
MAX-ACCESS  read-only
STATUS      current
DESCRIPTION
"High Input"
 ::= { ne843RecEntry  29 }

ne843RecEntryBof OBJECT-TYPE
SYNTAX      DisplayString
MAX-ACCESS  read-only
STATUS      current
DESCRIPTION
"ORing FET Fault"
 ::= { ne843RecEntry  30 }

ne843RecEntrySof OBJECT-TYPE
SYNTAX      DisplayString
MAX-ACCESS  read-only
STATUS      current
DESCRIPTION
"Shorted ORing FET"
 ::= { ne843RecEntry  31 }

ne843RecEntryDer OBJECT-TYPE
SYNTAX      DisplayString
MAX-ACCESS  read-only
STATUS      current
DESCRIPTION
"Under Voltage"
 ::= { ne843RecEntry  32 }

ne843RecEntryEcap OBJECT-TYPE
SYNTAX      Integer32
UNITS       "Amps"
MAX-ACCESS  read-only
STATUS      current
DESCRIPTION
"ECO Capacity (Amps)"
 ::= { ne843RecEntry  33 }

ne843RecEntryEmod OBJECT-TYPE
SYNTAX      Integer32
MAX-ACCESS  read-only
STATUS      current
DESCRIPTION
"ECO Mode"
 ::= { ne843RecEntry  34 }

ne843RecEntryMppt OBJECT-TYPE
SYNTAX      Integer32
MAX-ACCESS  read-only
STATUS      current
DESCRIPTION
"ECO MPPT"
 ::= { ne843RecEntry  35 }

ne843RecEntryRtm OBJECT-TYPE
SYNTAX      Integer32
MAX-ACCESS  read-only
STATUS      current
DESCRIPTION
"Run Time"
 ::= { ne843RecEntry  36 }

ne843RecEntryVan OBJECT-TYPE
SYNTAX      Integer32
MAX-ACCESS  read-only
STATUS      current
DESCRIPTION
"Anode Voltage"
 ::= { ne843RecEntry  37 }

ne843RecEntryVac1 OBJECT-TYPE
SYNTAX      Integer32
UNITS       "Volts"
MAX-ACCESS  read-only
STATUS      current
DESCRIPTION
"AC Voltage (Volts) Phase 1"
 ::= { ne843RecEntry  38 }

ne843RecEntryAac1 OBJECT-TYPE
SYNTAX      Integer32
UNITS       "mA"
MAX-ACCESS  read-only
STATUS      current
DESCRIPTION
"AC Current (mA) Phase 1"
 ::= { ne843RecEntry  39 }

ne843RecEntryVac2 OBJECT-TYPE
SYNTAX      Integer32
UNITS       "Volts"
MAX-ACCESS  read-only
STATUS      current
DESCRIPTION
"AC Voltage (Volts) Phase 2"
 ::= { ne843RecEntry  40 }

ne843RecEntryAac2 OBJECT-TYPE
SYNTAX      Integer32
UNITS       "mA"
MAX-ACCESS  read-only
STATUS      current
DESCRIPTION
"AC Current (mA) Phase 2"
 ::= { ne843RecEntry  41 }

ne843RecEntryVac3 OBJECT-TYPE
SYNTAX      Integer32
UNITS       "Volts"
MAX-ACCESS  read-only
STATUS      current
DESCRIPTION
"AC Voltage (Volts) Phase 3"
 ::= { ne843RecEntry  42 }

ne843RecEntryAac3 OBJECT-TYPE
SYNTAX      Integer32
UNITS       "mA"
MAX-ACCESS  read-only
STATUS      current
DESCRIPTION
"AC Current (mA) Phase 3"
 ::= { ne843RecEntry  43 }

ne843RecEntryRfa1 OBJECT-TYPE
SYNTAX      INTEGER {
inactive(0),
active(1)
}
MAX-ACCESS  read-only
STATUS      current
DESCRIPTION
"Rectifier Fail
Values:
inactive(0),
active(1)
"
 ::= { ne843RecEntry  44 }

ne843RecEntryAcf1 OBJECT-TYPE
SYNTAX      INTEGER {
inactive(0),
active(1)
}
MAX-ACCESS  read-only
STATUS      current
DESCRIPTION
"AC Fail
Values:
inactive(0),
active(1)
"
 ::= { ne843RecEntry  45 }

ne843RecEntryMan1 OBJECT-TYPE
SYNTAX      INTEGER {
inactive(0),
active(1)
}
MAX-ACCESS  read-only
STATUS      current
DESCRIPTION
"Standby or Manual Off
Values:
inactive(0),
active(1)
"
 ::= { ne843RecEntry  46 }

ne843RecEntryDid1 OBJECT-TYPE
SYNTAX      INTEGER {
inactive(0),
active(1)
}
MAX-ACCESS  read-only
STATUS      current
DESCRIPTION
"ID Conflict
Values:
inactive(0),
active(1)
"
 ::= { ne843RecEntry  47 }

ne843RecEntryClm1 OBJECT-TYPE
SYNTAX      INTEGER {
inactive(0),
active(1)
}
MAX-ACCESS  read-only
STATUS      current
DESCRIPTION
"Current Limit
Values:
inactive(0),
active(1)
"
 ::= { ne843RecEntry  48 }

ne843RecEntryRcf1 OBJECT-TYPE
SYNTAX      INTEGER {
inactive(0),
active(1)
}
MAX-ACCESS  read-only
STATUS      current
DESCRIPTION
"Communication Failure
Values:
inactive(0),
active(1)
"
 ::= { ne843RecEntry  49 }

ne843RecEntryRfn1 OBJECT-TYPE
SYNTAX      INTEGER {
inactive(0),
active(1)
}
MAX-ACCESS  read-only
STATUS      current
DESCRIPTION
"Fan Failure
Values:
inactive(0),
active(1)
"
 ::= { ne843RecEntry  50 }

ne843RecEntryRif1 OBJECT-TYPE
SYNTAX      INTEGER {
inactive(0),
active(1)
}
MAX-ACCESS  read-only
STATUS      current
DESCRIPTION
"Internal Fault
Values:
inactive(0),
active(1)
"
 ::= { ne843RecEntry  51 }

ne843RecEntryLsf1 OBJECT-TYPE
SYNTAX      INTEGER {
inactive(0),
active(1)
}
MAX-ACCESS  read-only
STATUS      current
DESCRIPTION
"Loadshare Failure
Values:
inactive(0),
active(1)
"
 ::= { ne843RecEntry  52 }

ne843RecEntryLin1 OBJECT-TYPE
SYNTAX      INTEGER {
inactive(0),
active(1)
}
MAX-ACCESS  read-only
STATUS      current
DESCRIPTION
"Low Input
Values:
inactive(0),
active(1)
"
 ::= { ne843RecEntry  53 }

ne843RecEntryHin1 OBJECT-TYPE
SYNTAX      INTEGER {
inactive(0),
active(1)
}
MAX-ACCESS  read-only
STATUS      current
DESCRIPTION
"High Input
Values:
inactive(0),
active(1)
"
 ::= { ne843RecEntry  54 }

ne843RecEntryBof1 OBJECT-TYPE
SYNTAX      INTEGER {
inactive(0),
active(1)
}
MAX-ACCESS  read-only
STATUS      current
DESCRIPTION
"ORing FET Fault
Values:
inactive(0),
active(1)
"
 ::= { ne843RecEntry  55 }

ne843RecEntrySof1 OBJECT-TYPE
SYNTAX      INTEGER {
inactive(0),
active(1)
}
MAX-ACCESS  read-only
STATUS      current
DESCRIPTION
"Shorted ORing FET
Values:
inactive(0),
active(1)
"
 ::= { ne843RecEntry  56 }

ne843RecEntryDer1 OBJECT-TYPE
SYNTAX      INTEGER {
inactive(0),
active(1)
}
MAX-ACCESS  read-only
STATUS      current
DESCRIPTION
"Under Voltage
Values:
inactive(0),
active(1)
"
 ::= { ne843RecEntry  57 }



--
-- object ne843Cp1
--

ne843Cp1 OBJECT IDENTIFIER  ::= { ne843  8 }

ne843Cp1Ide OBJECT-TYPE
SYNTAX      DisplayString
MAX-ACCESS  read-only
STATUS      current
DESCRIPTION
"Identifier"
 ::= { ne843Cp1  1 }

ne843Cp1Des OBJECT-TYPE
SYNTAX      DisplayString
MAX-ACCESS  read-write
STATUS      current
DESCRIPTION
"Description"
 ::= { ne843Cp1  2 }

ne843Cp1Typ OBJECT-TYPE
SYNTAX      DisplayString
MAX-ACCESS  read-only
STATUS      current
DESCRIPTION
"Type"
 ::= { ne843Cp1  3 }

ne843Cp1Vdc OBJECT-TYPE
SYNTAX      Integer32
UNITS       "mV"
MAX-ACCESS  read-only
STATUS      current
DESCRIPTION
"DC Voltage (mV)"
 ::= { ne843Cp1  4 }

ne843Cp1Adc OBJECT-TYPE
SYNTAX      Integer32
UNITS       "Amps"
MAX-ACCESS  read-only
STATUS      current
DESCRIPTION
"DC Current (Amps)"
 ::= { ne843Cp1  5 }

ne843Cp1Cap OBJECT-TYPE
SYNTAX      Integer32
UNITS       "Amps"
MAX-ACCESS  read-only
STATUS      current
DESCRIPTION
"Capacity (Amps)"
 ::= { ne843Cp1  6 }

ne843Cp1Olcap OBJECT-TYPE
SYNTAX      Integer32
UNITS       "Amps"
MAX-ACCESS  read-only
STATUS      current
DESCRIPTION
"On Line Capacity (Amps)"
 ::= { ne843Cp1  7 }

ne843Cp1Vsp OBJECT-TYPE
SYNTAX      Integer32(23000..28000|46000..57000)
UNITS       "mV"
MAX-ACCESS  read-write
STATUS      current
DESCRIPTION
"Voltage Set Point (mV)"
 ::= { ne843Cp1  8 }

ne843Cp1Vsd OBJECT-TYPE
SYNTAX      Integer32(25000..30000|50000..60000)
UNITS       "mV"
MAX-ACCESS  read-write
STATUS      current
DESCRIPTION
"Internal High Voltage Shutdown (mV)"
 ::= { ne843Cp1  9 }

ne843Cp1Clm OBJECT-TYPE
SYNTAX      Integer32(30..100)
UNITS       "%"
MAX-ACCESS  read-write
STATUS      current
DESCRIPTION
"Current Limit (%)"
 ::= { ne843Cp1  10 }

ne843Cp1Dth OBJECT-TYPE
SYNTAX      Integer32(20000..25000|40000..50000)
UNITS       "mV"
MAX-ACCESS  read-write
STATUS      current
DESCRIPTION
"Low Voltage Disconnect (mV)"
 ::= { ne843Cp1  11 }

ne843Cp1Rth OBJECT-TYPE
SYNTAX      Integer32(22000..27000|44000..54000)
UNITS       "mV"
MAX-ACCESS  read-write
STATUS      current
DESCRIPTION
"Low Voltage Reconnect (mV)"
 ::= { ne843Cp1  12 }

ne843Cp1Lvd OBJECT-TYPE
SYNTAX      INTEGER {
disable(0),
enable(1)
}
MAX-ACCESS  read-write
STATUS      current
DESCRIPTION
"Low Voltage Disconnect Enable
Values:
disable(0),
enable(1)
"
 ::= { ne843Cp1  13 }

ne843Cp1Rss OBJECT-TYPE
SYNTAX      INTEGER {
off(0),
on(1)
}
MAX-ACCESS  read-write
STATUS      current
DESCRIPTION
"Converter Restart
Values:
off(0),
on(1)
"
 ::= { ne843Cp1  14 }

ne843Cp1Rme OBJECT-TYPE
SYNTAX      INTEGER {
disable(0),
enable(1)
}
MAX-ACCESS  read-write
STATUS      current
DESCRIPTION
"Redundancy Monitor Enable
Values:
disable(0),
enable(1)
"
 ::= { ne843Cp1  15 }

ne843Cp1Rof OBJECT-TYPE
SYNTAX      INTEGER {
disable(0),
enable(1)
}
MAX-ACCESS  read-write
STATUS      current
DESCRIPTION
"Remote Standby Enable
Values:
disable(0),
enable(1)
"
 ::= { ne843Cp1  16 }

ne843Cp1Cfa OBJECT-TYPE
SYNTAX      DisplayString
MAX-ACCESS  read-only
STATUS      current
DESCRIPTION
"Converter Fail
Value:
Alarm report from CFA1
"
 ::= { ne843Cp1  17 }

ne843Cp1Cfn OBJECT-TYPE
SYNTAX      DisplayString
MAX-ACCESS  read-only
STATUS      current
DESCRIPTION
"Converter Fan Minor
Value:
Alarm report from CFN1
"
 ::= { ne843Cp1  18 }

ne843Cp1Cfj OBJECT-TYPE
SYNTAX      DisplayString
MAX-ACCESS  read-only
STATUS      current
DESCRIPTION
"Converter Fan Major
Value:
Alarm report from CFJ1
"
 ::= { ne843Cp1  19 }

ne843Cp1Dfa OBJECT-TYPE
SYNTAX      DisplayString
MAX-ACCESS  read-only
STATUS      current
DESCRIPTION
"Distribution Fail
Value:
Alarm report from CDFA1
"
 ::= { ne843Cp1  20 }

ne843Cp1Did OBJECT-TYPE
SYNTAX      DisplayString
MAX-ACCESS  read-only
STATUS      current
DESCRIPTION
"ID Conflict
Value:
Alarm report from CDID1
"
 ::= { ne843Cp1  21 }

ne843Cp1Icc OBJECT-TYPE
SYNTAX      DisplayString
MAX-ACCESS  read-only
STATUS      current
DESCRIPTION
"Incompatible Converter Alarm
Value:
Alarm report from ICC1
"
 ::= { ne843Cp1  22 }

ne843Cp1Mfa OBJECT-TYPE
SYNTAX      DisplayString
MAX-ACCESS  read-only
STATUS      current
DESCRIPTION
"Multiple Converter Fail
Value:
Alarm report from CMFA1
"
 ::= { ne843Cp1  23 }

ne843Cp1Hva OBJECT-TYPE
SYNTAX      DisplayString
MAX-ACCESS  read-only
STATUS      current
DESCRIPTION
"Converter High Voltage Major
Value:
Alarm report from CHVA1
"
 ::= { ne843Cp1  24 }

ne843Cp1Hfv OBJECT-TYPE
SYNTAX      DisplayString
MAX-ACCESS  read-only
STATUS      current
DESCRIPTION
"Converter High Voltage Minor
Value:
Alarm report from CHFV1
"
 ::= { ne843Cp1  25 }

ne843Cp1Vla OBJECT-TYPE
SYNTAX      DisplayString
MAX-ACCESS  read-only
STATUS      current
DESCRIPTION
"Converter Very Low Voltage
Value:
Alarm report from CVLA
"
 ::= { ne843Cp1  26 }

ne843Cp1Rl OBJECT-TYPE
SYNTAX      DisplayString
MAX-ACCESS  read-only
STATUS      current
DESCRIPTION
"Converter Redundancy Loss
Value:
Alarm report from CRL
"
 ::= { ne843Cp1  27 }

ne843Cp1Cin OBJECT-TYPE
SYNTAX      DisplayString
MAX-ACCESS  read-only
STATUS      current
DESCRIPTION
"Converter Input Fail
Value:
Alarm report from CIN1
"
 ::= { ne843Cp1  28 }


--
-- table DCC
--

ne843DccTable    OBJECT-TYPE
SYNTAX SEQUENCE OF Ne843DccEntry
MAX-ACCESS not-accessible
STATUS current
DESCRIPTION
        "Table of all Converter data"
 ::= { ne843  9 }

ne843DccEntry OBJECT-TYPE
SYNTAX     Ne843DccEntry
MAX-ACCESS  not-accessible
STATUS      current
DESCRIPTION
       "Entry of information for one Converter"
INDEX { ne843DccEntryIndex }
 ::= { ne843DccTable  1 }

Ne843DccEntry ::= SEQUENCE {
ne843DccEntryIndex   INTEGER,
ne843DccEntryIde   DisplayString,
ne843DccEntryDes   DisplayString,
ne843DccEntryTyp   DisplayString,
ne843DccEntrySn   DisplayString,
ne843DccEntryAdc   Integer32,
ne843DccEntryCap   Integer32,
ne843DccEntryStt   DisplayString,
ne843DccEntryCfa   DisplayString,
ne843DccEntryDfa   DisplayString,
ne843DccEntryDid   DisplayString,
ne843DccEntryCcf   DisplayString,
ne843DccEntryCfn   DisplayString,
ne843DccEntryCfa1   INTEGER,
ne843DccEntryDfa1   INTEGER,
ne843DccEntryDid1   INTEGER,
ne843DccEntryCcf1   INTEGER,
ne843DccEntryCfn1   INTEGER
}

ne843DccEntryIndex OBJECT-TYPE
SYNTAX      INTEGER (0..2147483647)
MAX-ACCESS  read-only
STATUS      current
DESCRIPTION
"Table Index"
 ::= { ne843DccEntry  1 }

ne843DccEntryIde OBJECT-TYPE
SYNTAX      DisplayString
MAX-ACCESS  read-only
STATUS      current
DESCRIPTION
"Identifier"
 ::= { ne843DccEntry  2 }

ne843DccEntryDes OBJECT-TYPE
SYNTAX      DisplayString
MAX-ACCESS  read-write
STATUS      current
DESCRIPTION
"Description"
 ::= { ne843DccEntry  3 }

ne843DccEntryTyp OBJECT-TYPE
SYNTAX      DisplayString
MAX-ACCESS  read-only
STATUS      current
DESCRIPTION
"Type"
 ::= { ne843DccEntry  4 }

ne843DccEntrySn OBJECT-TYPE
SYNTAX      DisplayString
MAX-ACCESS  read-only
STATUS      current
DESCRIPTION
"Serial Number"
 ::= { ne843DccEntry  5 }

ne843DccEntryAdc OBJECT-TYPE
SYNTAX      Integer32
UNITS       "Amps"
MAX-ACCESS  read-only
STATUS      current
DESCRIPTION
"DC Current (Amps)"
 ::= { ne843DccEntry  6 }

ne843DccEntryCap OBJECT-TYPE
SYNTAX      Integer32
UNITS       "Amps"
MAX-ACCESS  read-only
STATUS      current
DESCRIPTION
"Capacity (Amps)"
 ::= { ne843DccEntry  7 }

ne843DccEntryStt OBJECT-TYPE
SYNTAX      DisplayString
MAX-ACCESS  read-write
STATUS      current
DESCRIPTION
"State
Values:
ON,
OFF,
STANDBY,
VACANT
"
 ::= { ne843DccEntry  8 }

ne843DccEntryCfa OBJECT-TYPE
SYNTAX      DisplayString
MAX-ACCESS  read-only
STATUS      current
DESCRIPTION
"Converter Fail"
 ::= { ne843DccEntry  9 }

ne843DccEntryDfa OBJECT-TYPE
SYNTAX      DisplayString
MAX-ACCESS  read-only
STATUS      current
DESCRIPTION
"Distribution Fuse Fail"
 ::= { ne843DccEntry  10 }

ne843DccEntryDid OBJECT-TYPE
SYNTAX      DisplayString
MAX-ACCESS  read-only
STATUS      current
DESCRIPTION
"ID Conflict"
 ::= { ne843DccEntry  11 }

ne843DccEntryCcf OBJECT-TYPE
SYNTAX      DisplayString
MAX-ACCESS  read-only
STATUS      current
DESCRIPTION
"Communication Failure"
 ::= { ne843DccEntry  12 }

ne843DccEntryCfn OBJECT-TYPE
SYNTAX      DisplayString
MAX-ACCESS  read-only
STATUS      current
DESCRIPTION
"Fan Failure"
 ::= { ne843DccEntry  13 }

ne843DccEntryCfa1 OBJECT-TYPE
SYNTAX      INTEGER {
inactive(0),
active(1)
}
MAX-ACCESS  read-only
STATUS      current
DESCRIPTION
"Converter Fail
Values:
inactive(0),
active(1)
"
 ::= { ne843DccEntry  14 }

ne843DccEntryDfa1 OBJECT-TYPE
SYNTAX      INTEGER {
inactive(0),
active(1)
}
MAX-ACCESS  read-only
STATUS      current
DESCRIPTION
"Distribution Fuse Fail
Values:
inactive(0),
active(1)
"
 ::= { ne843DccEntry  15 }

ne843DccEntryDid1 OBJECT-TYPE
SYNTAX      INTEGER {
inactive(0),
active(1)
}
MAX-ACCESS  read-only
STATUS      current
DESCRIPTION
"ID Conflict
Values:
inactive(0),
active(1)
"
 ::= { ne843DccEntry  16 }

ne843DccEntryCcf1 OBJECT-TYPE
SYNTAX      INTEGER {
inactive(0),
active(1)
}
MAX-ACCESS  read-only
STATUS      current
DESCRIPTION
"Communication Failure
Values:
inactive(0),
active(1)
"
 ::= { ne843DccEntry  17 }

ne843DccEntryCfn1 OBJECT-TYPE
SYNTAX      INTEGER {
inactive(0),
active(1)
}
MAX-ACCESS  read-only
STATUS      current
DESCRIPTION
"Fan Failure Rev
Values:
inactive(0),
active(1)
"
 ::= { ne843DccEntry  18 }



--
-- object ne843Bs1
--

ne843Bs1 OBJECT IDENTIFIER  ::= { ne843  10 }

ne843Bs1Ide OBJECT-TYPE
SYNTAX      DisplayString
MAX-ACCESS  read-only
STATUS      current
DESCRIPTION
"Identifier"
 ::= { ne843Bs1  1 }

ne843Bs1Des OBJECT-TYPE
SYNTAX      DisplayString
MAX-ACCESS  read-write
STATUS      current
DESCRIPTION
"Description"
 ::= { ne843Bs1  2 }

ne843Bs1Stt OBJECT-TYPE
SYNTAX      DisplayString
MAX-ACCESS  read-only
STATUS      current
DESCRIPTION
"State
Values:
QRCT,
MANUAL,
BTP,
TIMED AUTO,
OFF
"
 ::= { ne843Bs1  3 }

ne843Bs1Atm OBJECT-TYPE
SYNTAX      DisplayString
MAX-ACCESS  read-write
STATUS      current
DESCRIPTION
"Auto Mode
Values:
OFF,
QRCT,
TIMED
"
 ::= { ne843Bs1  4 }

ne843Bs1Tmd OBJECT-TYPE
SYNTAX      Integer32(1..80)
UNITS       "Hours"
MAX-ACCESS  read-write
STATUS      current
DESCRIPTION
"Timed Manual Duration (Hours)"
 ::= { ne843Bs1  5 }

ne843Bs1Amf OBJECT-TYPE
SYNTAX      Integer32(1..9)
MAX-ACCESS  read-write
STATUS      current
DESCRIPTION
"Auto Multiplication Factor"
 ::= { ne843Bs1  6 }

ne843Bs1Cta OBJECT-TYPE
SYNTAX      Integer32(0..999)
MAX-ACCESS  read-write
STATUS      current
DESCRIPTION
"Current Terminated Current Threshold"
 ::= { ne843Bs1  7 }


--
-- object ne843Sc1
--

ne843Sc1 OBJECT IDENTIFIER  ::= { ne843  11 }

ne843Sc1Ide OBJECT-TYPE
SYNTAX      DisplayString
MAX-ACCESS  read-only
STATUS      current
DESCRIPTION
"Identifier"
 ::= { ne843Sc1  1 }

ne843Sc1Des OBJECT-TYPE
SYNTAX      DisplayString
MAX-ACCESS  read-write
STATUS      current
DESCRIPTION
"Description"
 ::= { ne843Sc1  2 }

ne843Sc1Stt OBJECT-TYPE
SYNTAX      INTEGER {
disable(0),
enable(1)
}
MAX-ACCESS  read-write
STATUS      current
DESCRIPTION
"State
Values:
disable(0),
enable(1)
"
 ::= { ne843Sc1  3 }

ne843Sc1Rve OBJECT-TYPE
SYNTAX      INTEGER {
disable(0),
enable(1)
}
MAX-ACCESS  read-write
STATUS      current
DESCRIPTION
"Raise Voltage Enable
Values:
disable(0),
enable(1)
"
 ::= { ne843Sc1  4 }

ne843Sc1Ltt OBJECT-TYPE
SYNTAX      Integer32
UNITS       "C"
MAX-ACCESS  read-write
STATUS      current
DESCRIPTION
"Lower Temperature Threshold (C)"
 ::= { ne843Sc1  5 }

ne843Sc1Ntt OBJECT-TYPE
SYNTAX      Integer32
UNITS       "C"
MAX-ACCESS  read-write
STATUS      current
DESCRIPTION
"Nominal Temperature Threshold (C)"
 ::= { ne843Sc1  6 }

ne843Sc1Utt OBJECT-TYPE
SYNTAX      Integer32
UNITS       "C"
MAX-ACCESS  read-write
STATUS      current
DESCRIPTION
"Upper Temperature Threshold (C)"
 ::= { ne843Sc1  7 }

ne843Sc1Spt OBJECT-TYPE
SYNTAX      Integer32
UNITS       "C"
MAX-ACCESS  read-write
STATUS      current
DESCRIPTION
"Step Temperature (C)"
 ::= { ne843Sc1  8 }

ne843Sc1Lsp OBJECT-TYPE
SYNTAX      Integer32(1..10)
UNITS       "mV/C"
MAX-ACCESS  read-write
STATUS      current
DESCRIPTION
"Lower Temperature Slope/Cell (mV/C)"
 ::= { ne843Sc1  9 }

ne843Sc1Usp OBJECT-TYPE
SYNTAX      Integer32(1..10)
UNITS       "mV/C"
MAX-ACCESS  read-write
STATUS      current
DESCRIPTION
"Upper Temperature Slope/Cell (mV/C)"
 ::= { ne843Sc1  10 }

ne843Sc1Fse OBJECT-TYPE
SYNTAX      INTEGER {
disable(0),
enable(1)
}
MAX-ACCESS  read-write
STATUS      current
DESCRIPTION
"Probe Fail-Safe Enable
Values:
disable(0),
enable(1)
"
 ::= { ne843Sc1  11 }


--
-- table BTD
--

ne843BtdTable    OBJECT-TYPE
SYNTAX SEQUENCE OF Ne843BtdEntry
MAX-ACCESS not-accessible
STATUS current
DESCRIPTION
        "Table of all Battery Type Definition data"
 ::= { ne843  12 }

ne843BtdEntry OBJECT-TYPE
SYNTAX     Ne843BtdEntry
MAX-ACCESS  not-accessible
STATUS      current
DESCRIPTION
       "Entry of information for one Battery Type Definition"
INDEX { ne843BtdEntryIndex }
 ::= { ne843BtdTable  1 }

Ne843BtdEntry ::= SEQUENCE {
ne843BtdEntryIndex   INTEGER,
ne843BtdEntryIde   DisplayString,
ne843BtdEntryDes   DisplayString,
ne843BtdEntryBty   DisplayString,
ne843BtdEntryBtc   DisplayString,
ne843BtdEntryCap   Integer32
}

ne843BtdEntryIndex OBJECT-TYPE
SYNTAX      INTEGER (0..2147483647)
MAX-ACCESS  read-only
STATUS      current
DESCRIPTION
"Table Index"
 ::= { ne843BtdEntry  1 }

ne843BtdEntryIde OBJECT-TYPE
SYNTAX      DisplayString
MAX-ACCESS  read-only
STATUS      current
DESCRIPTION
"Identifier"
 ::= { ne843BtdEntry  2 }

ne843BtdEntryDes OBJECT-TYPE
SYNTAX      DisplayString
MAX-ACCESS  read-write
STATUS      current
DESCRIPTION
"Description"
 ::= { ne843BtdEntry  3 }

ne843BtdEntryBty OBJECT-TYPE
SYNTAX      DisplayString
MAX-ACCESS  read-write
STATUS      current
DESCRIPTION
"Battery Type"
 ::= { ne843BtdEntry  4 }

ne843BtdEntryBtc OBJECT-TYPE
SYNTAX      DisplayString
MAX-ACCESS  read-write
STATUS      current
DESCRIPTION
"Battery Class
Values:
FLOODED,
SEALED,
NICD,
LI_LMP,
SODIUM
"
 ::= { ne843BtdEntry  5 }

ne843BtdEntryCap OBJECT-TYPE
SYNTAX      Integer32
UNITS       "Amps"
MAX-ACCESS  read-write
STATUS      current
DESCRIPTION
"Capacity (Amps)"
 ::= { ne843BtdEntry  6 }



--
-- object ne843Br1
--

ne843Br1 OBJECT IDENTIFIER  ::= { ne843  13 }

ne843Br1Ide OBJECT-TYPE
SYNTAX      DisplayString
MAX-ACCESS  read-only
STATUS      current
DESCRIPTION
"Identifier"
 ::= { ne843Br1  1 }

ne843Br1Des OBJECT-TYPE
SYNTAX      DisplayString
MAX-ACCESS  read-write
STATUS      current
DESCRIPTION
"Description"
 ::= { ne843Br1  2 }

ne843Br1Adc OBJECT-TYPE
SYNTAX      Integer32
UNITS       "Amps"
MAX-ACCESS  read-only
STATUS      current
DESCRIPTION
"Total Battery Current (Amps)"
 ::= { ne843Br1  3 }

ne843Br1Hbt OBJECT-TYPE
SYNTAX      Integer32
UNITS       "C"
MAX-ACCESS  read-only
STATUS      current
DESCRIPTION
"Highest Battery Temperature (C)"
 ::= { ne843Br1  4 }

ne843Br1Cap OBJECT-TYPE
SYNTAX      Integer32
UNITS       "Amps"
MAX-ACCESS  read-only
STATUS      current
DESCRIPTION
"Installed Battery Capacity (Amps)"
 ::= { ne843Br1  5 }

ne843Br1Olcap OBJECT-TYPE
SYNTAX      Integer32
UNITS       "Amps"
MAX-ACCESS  read-only
STATUS      current
DESCRIPTION
"On-line Battery Capacity (Amps)"
 ::= { ne843Br1  6 }

ne843Br1Btr OBJECT-TYPE
SYNTAX      DisplayString
MAX-ACCESS  read-only
STATUS      current
DESCRIPTION
"Battery Test Results"
 ::= { ne843Br1  7 }

ne843Br1Tth OBJECT-TYPE
SYNTAX      Integer32(30..194)
UNITS       "C"
MAX-ACCESS  read-write
STATUS      current
DESCRIPTION
"High Temperature Threshold (C)"
 ::= { ne843Br1  8 }

ne843Br1Cle OBJECT-TYPE
SYNTAX      INTEGER {
disable(0),
enable(1)
}
MAX-ACCESS  read-write
STATUS      current
DESCRIPTION
"Current Limit Enable
Values:
disable(0),
enable(1)
"
 ::= { ne843Br1  9 }

ne843Br1Clt OBJECT-TYPE
SYNTAX      Integer32(10..1000)
UNITS       "Amps"
MAX-ACCESS  read-write
STATUS      current
DESCRIPTION
"Current Limit Threshold (Amps)"
 ::= { ne843Br1  10 }

ne843Br1Cev OBJECT-TYPE
SYNTAX      Integer32(19250..22750|40250..43750)
UNITS       "mV"
MAX-ACCESS  read-write
STATUS      current
DESCRIPTION
"End Volts per Cell (mV)"
 ::= { ne843Br1  11 }

ne843Br1Bts OBJECT-TYPE
SYNTAX      INTEGER {
inactive(0),
active(1)
}
MAX-ACCESS  read-write
STATUS      current
DESCRIPTION
"Battery Test State
Values:
inactive(0),
active(1)
"
 ::= { ne843Br1  12 }

ne843Br1Mtt OBJECT-TYPE
SYNTAX      DisplayString
MAX-ACCESS  read-write
STATUS      current
DESCRIPTION
"Manual Test Type
Values:
DISABLE,
20%,
TIMED
"
 ::= { ne843Br1  13 }

ne843Br1Tev OBJECT-TYPE
SYNTAX      Integer32(21000..27000|36000..48000)
UNITS       "mV"
MAX-ACCESS  read-write
STATUS      current
DESCRIPTION
"Manual Test Alarm Voltage (mV)"
 ::= { ne843Br1  14 }

ne843Br1Tmd OBJECT-TYPE
SYNTAX      Integer32(100..99900)
UNITS       "Hours x 1000"
MAX-ACCESS  read-write
STATUS      current
DESCRIPTION
"Manual Test Duration (Hours x 1000)"
 ::= { ne843Br1  15 }

ne843Br1Bte OBJECT-TYPE
SYNTAX      DisplayString
MAX-ACCESS  read-write
STATUS      current
DESCRIPTION
"Automatic Test Type
Values:
DISABLE,
20%,
TIMED
"
 ::= { ne843Br1  16 }

ne843Br1Btv OBJECT-TYPE
SYNTAX      Integer32(21000..26000|42000..52000)
UNITS       "mV"
MAX-ACCESS  read-write
STATUS      current
DESCRIPTION
"Battery Test Rectifier Voltage (mV)"
 ::= { ne843Br1  17 }

ne843Br1Ath OBJECT-TYPE
SYNTAX      Integer32(0..23)
MAX-ACCESS  read-write
STATUS      current
DESCRIPTION
"Auto Test Hour"
 ::= { ne843Br1  18 }

ne843Br1Tin OBJECT-TYPE
SYNTAX      Integer32(1..18)
UNITS       "Months"
MAX-ACCESS  read-write
STATUS      current
DESCRIPTION
"Auto Test Interval (Months)"
 ::= { ne843Br1  19 }

ne843Br1Atw OBJECT-TYPE
SYNTAX      Integer32(0..240)
UNITS       "Hours"
MAX-ACCESS  read-write
STATUS      current
DESCRIPTION
"Auto Test Minimum wait after BD (Hours)"
 ::= { ne843Br1  20 }

ne843Br1Atd OBJECT-TYPE
SYNTAX      DisplayString
MAX-ACCESS  read-write
STATUS      current
DESCRIPTION
"Auto Test Date"
 ::= { ne843Br1  21 }

ne843Br1Nvm OBJECT-TYPE
SYNTAX      Integer32
MAX-ACCESS  read-only
STATUS      current
DESCRIPTION
"Number of Mid-cell V Present"
 ::= { ne843Br1  22 }

ne843Br1Ntm OBJECT-TYPE
SYNTAX      Integer32
MAX-ACCESS  read-only
STATUS      current
DESCRIPTION
"Number of Temperature Probes Present"
 ::= { ne843Br1  23 }

ne843Br1Scd OBJECT-TYPE
SYNTAX      INTEGER {
disable(0),
enable(1)
}
MAX-ACCESS  read-only
STATUS      current
DESCRIPTION
"Battery Voltage Imbalance Detection
Values:
disable(0),
enable(1)
"
 ::= { ne843Br1  24 }

ne843Br1Scv OBJECT-TYPE
SYNTAX      Integer32(1500..3000)
UNITS       "mV"
MAX-ACCESS  read-write
STATUS      current
DESCRIPTION
"Battery Imbalance Threshold (mV)"
 ::= { ne843Br1  25 }

ne843Br1Bta OBJECT-TYPE
SYNTAX      DisplayString
MAX-ACCESS  read-only
STATUS      current
DESCRIPTION
"Battery Test Active
Value:
Alarm report from BTA1
"
 ::= { ne843Br1  26 }

ne843Br1Bfa OBJECT-TYPE
SYNTAX      DisplayString
MAX-ACCESS  read-only
STATUS      current
DESCRIPTION
"Battery Test Failed
Value:
Alarm report from BFA1
"
 ::= { ne843Br1  27 }

ne843Br1Scda OBJECT-TYPE
SYNTAX      DisplayString
MAX-ACCESS  read-only
STATUS      current
DESCRIPTION
"Shorted Cell Detected
Value:
Alarm report from SCD1
"
 ::= { ne843Br1  28 }

ne843Br1Isda OBJECT-TYPE
SYNTAX      DisplayString
MAX-ACCESS  read-only
STATUS      current
DESCRIPTION
"Imminent Shutdown
Value:
Alarm report from ISD1
"
 ::= { ne843Br1  29 }

ne843Br1Mdp OBJECT-TYPE
SYNTAX      DisplayString
MAX-ACCESS  read-only
STATUS      current
DESCRIPTION
"Voltage Duplicate ID
Value:
Alarm report from MDP1
"
 ::= { ne843Br1  30 }

ne843Br1Mzd OBJECT-TYPE
SYNTAX      DisplayString
MAX-ACCESS  read-only
STATUS      current
DESCRIPTION
"Voltage ID Not Configured
Value:
Alarm report from MZD1
"
 ::= { ne843Br1  31 }

ne843Br1Btha OBJECT-TYPE
SYNTAX      DisplayString
MAX-ACCESS  read-only
STATUS      current
DESCRIPTION
"High Battery Temperature
Value:
Alarm report from BTHA1
"
 ::= { ne843Br1  32 }

ne843Br1Lbt OBJECT-TYPE
SYNTAX      Integer32
UNITS       "C"
MAX-ACCESS  read-only
STATUS      current
DESCRIPTION
"Lowest Battery Temperature (C)"
 ::= { ne843Br1  33 }

ne843Br1Btla OBJECT-TYPE
SYNTAX      DisplayString
MAX-ACCESS  read-only
STATUS      current
DESCRIPTION
"Low Battery Temperature
Value:
Alarm report from BTLA1
"
 ::= { ne843Br1  34 }

ne843Br1Btvh OBJECT-TYPE
SYNTAX      DisplayString
MAX-ACCESS  read-only
STATUS      current
DESCRIPTION
"Very High Battery Temperature
Value:
Alarm report from BTVH1
"
 ::= { ne843Br1  35 }

ne843Br1Btvl OBJECT-TYPE
SYNTAX      DisplayString
MAX-ACCESS  read-only
STATUS      current
DESCRIPTION
"Very Low Battery Temperature
Value:
Alarm report from BTVL1
"
 ::= { ne843Br1  36 }

ne843Br1Rba OBJECT-TYPE
SYNTAX      DisplayString
MAX-ACCESS  read-only
STATUS      current
DESCRIPTION
"Reverse Battery
Value:
Alarm report from RBA1
"
 ::= { ne843Br1  37 }


--
-- table CNT
--

ne843CntTable    OBJECT-TYPE
SYNTAX SEQUENCE OF Ne843CntEntry
MAX-ACCESS not-accessible
STATUS current
DESCRIPTION
        "Table of all Contactor data"
 ::= { ne843  14 }

ne843CntEntry OBJECT-TYPE
SYNTAX     Ne843CntEntry
MAX-ACCESS  not-accessible
STATUS      current
DESCRIPTION
       "Entry of information for one Contactor"
INDEX { ne843CntEntryIndex }
 ::= { ne843CntTable  1 }

Ne843CntEntry ::= SEQUENCE {
ne843CntEntryIndex   INTEGER,
ne843CntEntryIde   DisplayString,
ne843CntEntryDes   DisplayString,
ne843CntEntryStt   DisplayString,
ne843CntEntryEna   INTEGER,
ne843CntEntryDth   Integer32,
ne843CntEntryDdy   DisplayString,
ne843CntEntryDam   INTEGER,
ne843CntEntryDtm   DisplayString,
ne843CntEntryRth   Integer32,
ne843CntEntryRdy   DisplayString,
ne843CntEntryRam   INTEGER,
ne843CntEntryRtm   DisplayString,
ne843CntEntryCno   DisplayString,
ne843CntEntryCnf   DisplayString,
ne843CntEntryDvx   Integer32,
ne843CntEntryDin   Integer32,
ne843CntEntryDix   Integer32,
ne843CntEntryDvt   Integer32,
ne843CntEntryDtd   DisplayString,
ne843CntEntryDtp   Integer32,
ne843CntEntryRtd   DisplayString,
ne843CntEntryRtp   Integer32
}

ne843CntEntryIndex OBJECT-TYPE
SYNTAX      INTEGER (0..2147483647)
MAX-ACCESS  read-only
STATUS      current
DESCRIPTION
"Table Index"
 ::= { ne843CntEntry  1 }

ne843CntEntryIde OBJECT-TYPE
SYNTAX      DisplayString
MAX-ACCESS  read-only
STATUS      current
DESCRIPTION
"Identifier"
 ::= { ne843CntEntry  2 }

ne843CntEntryDes OBJECT-TYPE
SYNTAX      DisplayString
MAX-ACCESS  read-write
STATUS      current
DESCRIPTION
"Description"
 ::= { ne843CntEntry  3 }

ne843CntEntryStt OBJECT-TYPE
SYNTAX      DisplayString
MAX-ACCESS  read-write
STATUS      current
DESCRIPTION
"Status
Values:
NONE,
DISCON,
CONNECT,
FAILED
"
 ::= { ne843CntEntry  4 }

ne843CntEntryEna OBJECT-TYPE
SYNTAX      INTEGER {
disable(0),
enable(1)
}
MAX-ACCESS  read-write
STATUS      current
DESCRIPTION
"Control
Values:
disable(0),
enable(1)
"
 ::= { ne843CntEntry  5 }

ne843CntEntryDth OBJECT-TYPE
SYNTAX      Integer32(19000..25000|39000..50000)
UNITS       "mV"
MAX-ACCESS  read-write
STATUS      current
DESCRIPTION
"Disconnect Threshold (mV)"
 ::= { ne843CntEntry  6 }

ne843CntEntryDdy OBJECT-TYPE
SYNTAX      DisplayString
MAX-ACCESS  read-write
STATUS      current
DESCRIPTION
"Disconnect Delay"
 ::= { ne843CntEntry  7 }

ne843CntEntryDam OBJECT-TYPE
SYNTAX      INTEGER {
none(0),
voltage(1),
voltageAndTime(2),
adaptive(3),
temperature(4),
voltageandtemperature(5),
voltageandtimeandtemperature(6),
adaptiveandtemperature(7)
}
MAX-ACCESS  read-write
STATUS      current
DESCRIPTION
"Disconnect Automode
Values:
none(0),
voltage(1),
voltageAndTime(2),
adaptive(3),
temperature(4),
voltageandtemperature(5),
voltageandtimeandtemperature(6),
adaptiveandtemperature(7)
"
 ::= { ne843CntEntry  8 }

ne843CntEntryDtm OBJECT-TYPE
SYNTAX      DisplayString
MAX-ACCESS  read-only
STATUS      current
DESCRIPTION
"Disconnect Time Remaining"
 ::= { ne843CntEntry  9 }

ne843CntEntryRth OBJECT-TYPE
SYNTAX      Integer32(19500..27000|39000..55000)
UNITS       "mV"
MAX-ACCESS  read-write
STATUS      current
DESCRIPTION
"Reconnect Threshold (mV)"
 ::= { ne843CntEntry  10 }

ne843CntEntryRdy OBJECT-TYPE
SYNTAX      DisplayString
MAX-ACCESS  read-write
STATUS      current
DESCRIPTION
"Reconnect Delay"
 ::= { ne843CntEntry  11 }

ne843CntEntryRam OBJECT-TYPE
SYNTAX      INTEGER {
none(0),
voltage(1),
voltageAndTime(2),
adaptive(3),
temperature(4),
voltageandtemperature(5),
voltageandtimeandtemperature(6),
adaptiveandtemperature(7)
}
MAX-ACCESS  read-write
STATUS      current
DESCRIPTION
"Reconnect Automode
Values:
none(0),
voltage(1),
voltageAndTime(2),
adaptive(3),
temperature(4),
voltageandtemperature(5),
voltageandtimeandtemperature(6),
adaptiveandtemperature(7)
"
 ::= { ne843CntEntry  12 }

ne843CntEntryRtm OBJECT-TYPE
SYNTAX      DisplayString
MAX-ACCESS  read-only
STATUS      current
DESCRIPTION
"Reconnect Time Remaining"
 ::= { ne843CntEntry  13 }

ne843CntEntryCno OBJECT-TYPE
SYNTAX      DisplayString
MAX-ACCESS  read-only
STATUS      current
DESCRIPTION
"Contactor Open"
 ::= { ne843CntEntry  14 }

ne843CntEntryCnf OBJECT-TYPE
SYNTAX      DisplayString
MAX-ACCESS  read-only
STATUS      current
DESCRIPTION
"Contactor Failed"
 ::= { ne843CntEntry  15 }

ne843CntEntryDvx OBJECT-TYPE
SYNTAX      Integer32(39000..50000)
UNITS       "mV"
MAX-ACCESS  read-write
STATUS      current
DESCRIPTION
"VMax in Adaptive Mode (mV)"
 ::= { ne843CntEntry  16 }

ne843CntEntryDin OBJECT-TYPE
SYNTAX      Integer32(0..9999000)
UNITS       "mA"
MAX-ACCESS  read-write
STATUS      current
DESCRIPTION
"IMin in Adaptive Mode (mA)"
 ::= { ne843CntEntry  17 }

ne843CntEntryDix OBJECT-TYPE
SYNTAX      Integer32(0..9999000)
UNITS       "mA"
MAX-ACCESS  read-write
STATUS      current
DESCRIPTION
"IMax in Adaptive Mode (mA)"
 ::= { ne843CntEntry  18 }

ne843CntEntryDvt OBJECT-TYPE
SYNTAX      Integer32
UNITS       "mV"
MAX-ACCESS  read-only
STATUS      current
DESCRIPTION
"Calculated Disconnect Voltage (mV)"
 ::= { ne843CntEntry  19 }

ne843CntEntryDtd OBJECT-TYPE
SYNTAX      DisplayString
MAX-ACCESS  read-write
STATUS      current
DESCRIPTION
"Disconnect Temperature Delay"
 ::= { ne843CntEntry  20 }

ne843CntEntryDtp OBJECT-TYPE
SYNTAX      Integer32(1125..5625)
MAX-ACCESS  read-write
STATUS      current
DESCRIPTION
"Disconnect Temperature"
 ::= { ne843CntEntry  21 }

ne843CntEntryRtd OBJECT-TYPE
SYNTAX      DisplayString
MAX-ACCESS  read-write
STATUS      current
DESCRIPTION
"Reconnect Temperature Delay"
 ::= { ne843CntEntry  22 }

ne843CntEntryRtp OBJECT-TYPE
SYNTAX      Integer32(1080..5400)
MAX-ACCESS  read-write
STATUS      current
DESCRIPTION
"Reconnect Temperature"
 ::= { ne843CntEntry  23 }



--
-- table DCN
--

ne843DcnTable    OBJECT-TYPE
SYNTAX SEQUENCE OF Ne843DcnEntry
MAX-ACCESS not-accessible
STATUS current
DESCRIPTION
        "Table of all Distribution Contactor Interface data"
 ::= { ne843  15 }

ne843DcnEntry OBJECT-TYPE
SYNTAX     Ne843DcnEntry
MAX-ACCESS  not-accessible
STATUS      current
DESCRIPTION
       "Entry of information for one Distribution Contactor Interface"
INDEX { ne843DcnEntryIndex }
 ::= { ne843DcnTable  1 }

Ne843DcnEntry ::= SEQUENCE {
ne843DcnEntryIndex   INTEGER,
ne843DcnEntryIde   DisplayString,
ne843DcnEntryDes   DisplayString,
ne843DcnEntryStt   DisplayString,
ne843DcnEntryTyp   DisplayString,
ne843DcnEntrySn   DisplayString,
ne843DcnEntryBrc   DisplayString
}

ne843DcnEntryIndex OBJECT-TYPE
SYNTAX      INTEGER (0..2147483647)
MAX-ACCESS  read-only
STATUS      current
DESCRIPTION
"Table Index"
 ::= { ne843DcnEntry  1 }

ne843DcnEntryIde OBJECT-TYPE
SYNTAX      DisplayString
MAX-ACCESS  read-only
STATUS      current
DESCRIPTION
"Identifier"
 ::= { ne843DcnEntry  2 }

ne843DcnEntryDes OBJECT-TYPE
SYNTAX      DisplayString
MAX-ACCESS  read-write
STATUS      current
DESCRIPTION
"Description"
 ::= { ne843DcnEntry  3 }

ne843DcnEntryStt OBJECT-TYPE
SYNTAX      DisplayString
MAX-ACCESS  read-only
STATUS      current
DESCRIPTION
"State
Values:
NONE,
MISSING,
PRESENT,
OPEN,
CLOSED
"
 ::= { ne843DcnEntry  4 }

ne843DcnEntryTyp OBJECT-TYPE
SYNTAX      DisplayString
MAX-ACCESS  read-write
STATUS      current
DESCRIPTION
"Contactor Interface Type
Values:
NONE,
CN1,
CN2,
CN3,
CN4
"
 ::= { ne843DcnEntry  5 }

ne843DcnEntrySn OBJECT-TYPE
SYNTAX      DisplayString
MAX-ACCESS  read-only
STATUS      current
DESCRIPTION
"Serial Number"
 ::= { ne843DcnEntry  6 }

ne843DcnEntryBrc OBJECT-TYPE
SYNTAX      DisplayString
MAX-ACCESS  read-only
STATUS      current
DESCRIPTION
"Board Code"
 ::= { ne843DcnEntry  7 }



--
-- table DCM
--

ne843DcmTable    OBJECT-TYPE
SYNTAX SEQUENCE OF Ne843DcmEntry
MAX-ACCESS not-accessible
STATUS current
DESCRIPTION
        "Table of all Distribution Current Monitor data"
 ::= { ne843  16 }

ne843DcmEntry OBJECT-TYPE
SYNTAX     Ne843DcmEntry
MAX-ACCESS  not-accessible
STATUS      current
DESCRIPTION
       "Entry of information for one Distribution Current Monitor"
INDEX { ne843DcmEntryIndex }
 ::= { ne843DcmTable  1 }

Ne843DcmEntry ::= SEQUENCE {
ne843DcmEntryIndex   INTEGER,
ne843DcmEntryIde   DisplayString,
ne843DcmEntryDes   DisplayString,
ne843DcmEntryStt   DisplayString,
ne843DcmEntryTyp   DisplayString,
ne843DcmEntryVal   Integer32,
ne843DcmEntrySha   Integer32,
ne843DcmEntrySn   DisplayString,
ne843DcmEntryBrc   DisplayString,
ne843DcmEntryKwh   DisplayString
}

ne843DcmEntryIndex OBJECT-TYPE
SYNTAX      INTEGER (0..2147483647)
MAX-ACCESS  read-only
STATUS      current
DESCRIPTION
"Table Index"
 ::= { ne843DcmEntry  1 }

ne843DcmEntryIde OBJECT-TYPE
SYNTAX      DisplayString
MAX-ACCESS  read-only
STATUS      current
DESCRIPTION
"Identifier"
 ::= { ne843DcmEntry  2 }

ne843DcmEntryDes OBJECT-TYPE
SYNTAX      DisplayString
MAX-ACCESS  read-write
STATUS      current
DESCRIPTION
"Description"
 ::= { ne843DcmEntry  3 }

ne843DcmEntryStt OBJECT-TYPE
SYNTAX      DisplayString
MAX-ACCESS  read-only
STATUS      current
DESCRIPTION
"State
Values:
NONE,
MISSING,
PRESENT
"
 ::= { ne843DcmEntry  4 }

ne843DcmEntryTyp OBJECT-TYPE
SYNTAX      DisplayString
MAX-ACCESS  read-write
STATUS      current
DESCRIPTION
"Shunt Type
Values:
NONE,
LOAD,
BATTERY
"
 ::= { ne843DcmEntry  5 }

ne843DcmEntryVal OBJECT-TYPE
SYNTAX      Integer32
UNITS       "mA"
MAX-ACCESS  read-only
STATUS      current
DESCRIPTION
"Reading (mA)"
 ::= { ne843DcmEntry  6 }

ne843DcmEntrySha OBJECT-TYPE
SYNTAX      Integer32
UNITS       "Amps"
MAX-ACCESS  read-write
STATUS      current
DESCRIPTION
"Shunt Rating (Amps)"
 ::= { ne843DcmEntry  7 }

ne843DcmEntrySn OBJECT-TYPE
SYNTAX      DisplayString
MAX-ACCESS  read-only
STATUS      current
DESCRIPTION
"Serial Number"
 ::= { ne843DcmEntry  8 }

ne843DcmEntryBrc OBJECT-TYPE
SYNTAX      DisplayString
MAX-ACCESS  read-only
STATUS      current
DESCRIPTION
"Board Code"
 ::= { ne843DcmEntry  9 }

ne843DcmEntryKwh OBJECT-TYPE
SYNTAX      DisplayString
UNITS       "kWh"
MAX-ACCESS  read-write
STATUS      current
DESCRIPTION
"Kilo Watt Hours (kWh)"
 ::= { ne843DcmEntry  10 }



--
-- table UDE
--

ne843UdeTable    OBJECT-TYPE
SYNTAX SEQUENCE OF Ne843UdeEntry
MAX-ACCESS not-accessible
STATUS current
DESCRIPTION
        "Table of all User Defined Event data"
 ::= { ne843  17 }

ne843UdeEntry OBJECT-TYPE
SYNTAX     Ne843UdeEntry
MAX-ACCESS  not-accessible
STATUS      current
DESCRIPTION
       "Entry of information for one User Defined Event"
INDEX { ne843UdeEntryIndex }
 ::= { ne843UdeTable  1 }

Ne843UdeEntry ::= SEQUENCE {
ne843UdeEntryIndex   INTEGER,
ne843UdeEntryIde   DisplayString,
ne843UdeEntryDes   DisplayString,
ne843UdeEntryFds   DisplayString,
ne843UdeEntryAst   DisplayString,
ne843UdeEntrySev   DisplayString,
ne843UdeEntryPrg   DisplayString,
ne843UdeEntryDur   DisplayString,
ne843UdeEntryLed   DisplayString,
ne843UdeEntryLat   INTEGER,
ne843UdeEntryAcc   DisplayString,
ne843UdeEntryDly   Integer32,
ne843UdeEntryNoo   INTEGER,
ne843UdeEntryNor   INTEGER,
ne843UdeEntryNag   INTEGER,
ne843UdeEntryDst   DisplayString,
ne843UdeEntryAst1   INTEGER
}

ne843UdeEntryIndex OBJECT-TYPE
SYNTAX      INTEGER (0..2147483647)
MAX-ACCESS  read-only
STATUS      current
DESCRIPTION
"Table Index"
 ::= { ne843UdeEntry  1 }

ne843UdeEntryIde OBJECT-TYPE
SYNTAX      DisplayString
MAX-ACCESS  read-only
STATUS      current
DESCRIPTION
"Identifier"
 ::= { ne843UdeEntry  2 }

ne843UdeEntryDes OBJECT-TYPE
SYNTAX      DisplayString
MAX-ACCESS  read-write
STATUS      current
DESCRIPTION
"Description"
 ::= { ne843UdeEntry  3 }

ne843UdeEntryFds OBJECT-TYPE
SYNTAX      DisplayString
MAX-ACCESS  read-write
STATUS      current
DESCRIPTION
"Front Panel Description"
 ::= { ne843UdeEntry  4 }

ne843UdeEntryAst OBJECT-TYPE
SYNTAX      DisplayString
MAX-ACCESS  read-only
STATUS      current
DESCRIPTION
"Alarm State"
 ::= { ne843UdeEntry  5 }

ne843UdeEntrySev OBJECT-TYPE
SYNTAX      DisplayString
MAX-ACCESS  read-write
STATUS      current
DESCRIPTION
"Severity
Values:
CRIT,
MAJ,
MIN,
WRN,
RO
"
 ::= { ne843UdeEntry  6 }

ne843UdeEntryPrg OBJECT-TYPE
SYNTAX      DisplayString
MAX-ACCESS  read-write
STATUS      current
DESCRIPTION
"Program Line"
 ::= { ne843UdeEntry  7 }

ne843UdeEntryDur OBJECT-TYPE
SYNTAX      DisplayString
MAX-ACCESS  read-write
STATUS      current
DESCRIPTION
"Minimum Duration"
 ::= { ne843UdeEntry  8 }

ne843UdeEntryLed OBJECT-TYPE
SYNTAX      DisplayString
MAX-ACCESS  read-write
STATUS      current
DESCRIPTION
"LED
Values:
BD,
AC,
DC,

"
 ::= { ne843UdeEntry  9 }

ne843UdeEntryLat OBJECT-TYPE
SYNTAX      INTEGER {
no(0),
yes(1)
}
MAX-ACCESS  read-write
STATUS      current
DESCRIPTION
"Latched
Values:
no(0),
yes(1)
"
 ::= { ne843UdeEntry  10 }

ne843UdeEntryAcc OBJECT-TYPE
SYNTAX      DisplayString
MAX-ACCESS  read-write
STATUS      current
DESCRIPTION
"Contact Closure
Values:
,
R1,
R2,
R3,
R4,
R5,
R6,
R7
"
 ::= { ne843UdeEntry  11 }

ne843UdeEntryDly OBJECT-TYPE
SYNTAX      Integer32(0..540)
UNITS       "Seconds"
MAX-ACCESS  read-write
STATUS      current
DESCRIPTION
"Notify Delay (Seconds)"
 ::= { ne843UdeEntry  12 }

ne843UdeEntryNoo OBJECT-TYPE
SYNTAX      INTEGER {
no(0),
yes(1)
}
MAX-ACCESS  read-write
STATUS      current
DESCRIPTION
"Notify on Occur
Values:
no(0),
yes(1)
"
 ::= { ne843UdeEntry  13 }

ne843UdeEntryNor OBJECT-TYPE
SYNTAX      INTEGER {
no(0),
yes(1)
}
MAX-ACCESS  read-write
STATUS      current
DESCRIPTION
"Notify on Retire
Values:
no(0),
yes(1)
"
 ::= { ne843UdeEntry  14 }

ne843UdeEntryNag OBJECT-TYPE
SYNTAX      INTEGER {
no(0),
yes(1)
}
MAX-ACCESS  read-write
STATUS      current
DESCRIPTION
"NAG on Occur
Values:
no(0),
yes(1)
"
 ::= { ne843UdeEntry  15 }

ne843UdeEntryDst OBJECT-TYPE
SYNTAX      DisplayString
MAX-ACCESS  read-write
STATUS      current
DESCRIPTION
"Notify Destination"
 ::= { ne843UdeEntry  16 }

ne843UdeEntryAst1 OBJECT-TYPE
SYNTAX      INTEGER {
inactive(0),
active(1)
}
MAX-ACCESS  read-only
STATUS      current
DESCRIPTION
"Alarm State
Values:
inactive(0),
active(1)
"
 ::= { ne843UdeEntry  17 }



--
-- object ne843Cm1
--

ne843Cm1 OBJECT IDENTIFIER  ::= { ne843  18 }

ne843Cm1Ide OBJECT-TYPE
SYNTAX      DisplayString
MAX-ACCESS  read-only
STATUS      current
DESCRIPTION
"Identifier"
 ::= { ne843Cm1  1 }

ne843Cm1Des OBJECT-TYPE
SYNTAX      DisplayString
MAX-ACCESS  read-write
STATUS      current
DESCRIPTION
"Description"
 ::= { ne843Cm1  2 }

ne843Cm1Ngi OBJECT-TYPE
SYNTAX      Integer32(15..60)
MAX-ACCESS  read-write
STATUS      current
DESCRIPTION
"Nag Interval"
 ::= { ne843Cm1  3 }

ne843Cm1Cof OBJECT-TYPE
SYNTAX      DisplayString
MAX-ACCESS  read-only
STATUS      current
DESCRIPTION
"Queue Overflow
Value:
Alarm report from COF1
"
 ::= { ne843Cm1  4 }

ne843Cm1Cor OBJECT-TYPE
SYNTAX      DisplayString
MAX-ACCESS  read-only
STATUS      current
DESCRIPTION
"Number Did Not Respond
Value:
Alarm report from COR1
"
 ::= { ne843Cm1  5 }

ne843Cm1Nnc OBJECT-TYPE
SYNTAX      DisplayString
MAX-ACCESS  read-only
STATUS      current
DESCRIPTION
"Number Not Configured
Value:
Alarm report from NNC1
"
 ::= { ne843Cm1  6 }


--
-- table COP
--

ne843CopTable    OBJECT-TYPE
SYNTAX SEQUENCE OF Ne843CopEntry
MAX-ACCESS not-accessible
STATUS current
DESCRIPTION
        "Table of all Call Out Phone Number data"
 ::= { ne843  19 }

ne843CopEntry OBJECT-TYPE
SYNTAX     Ne843CopEntry
MAX-ACCESS  not-accessible
STATUS      current
DESCRIPTION
       "Entry of information for one Call Out Phone Number"
INDEX { ne843CopEntryIndex }
 ::= { ne843CopTable  1 }

Ne843CopEntry ::= SEQUENCE {
ne843CopEntryIndex   INTEGER,
ne843CopEntryIde   DisplayString,
ne843CopEntryDes   DisplayString,
ne843CopEntryTyp   DisplayString,
ne843CopEntryPhn   DisplayString,
ne843CopEntryBdr   INTEGER,
ne843CopEntryDbt   INTEGER,
ne843CopEntryPry   DisplayString,
ne843CopEntrySbt   INTEGER,
ne843CopEntryDly   Integer32,
ne843CopEntryPgr   DisplayString,
ne843CopEntryMsg   DisplayString
}

ne843CopEntryIndex OBJECT-TYPE
SYNTAX      INTEGER (0..2147483647)
MAX-ACCESS  read-only
STATUS      current
DESCRIPTION
"Table Index"
 ::= { ne843CopEntry  1 }

ne843CopEntryIde OBJECT-TYPE
SYNTAX      DisplayString
MAX-ACCESS  read-only
STATUS      current
DESCRIPTION
"Identifier"
 ::= { ne843CopEntry  2 }

ne843CopEntryDes OBJECT-TYPE
SYNTAX      DisplayString
MAX-ACCESS  read-write
STATUS      current
DESCRIPTION
"Description"
 ::= { ne843CopEntry  3 }

ne843CopEntryTyp OBJECT-TYPE
SYNTAX      DisplayString
MAX-ACCESS  read-write
STATUS      current
DESCRIPTION
"Type
Values:
DATA,
PAGER
"
 ::= { ne843CopEntry  4 }

ne843CopEntryPhn OBJECT-TYPE
SYNTAX      DisplayString
MAX-ACCESS  read-write
STATUS      current
DESCRIPTION
"Phone Number"
 ::= { ne843CopEntry  5 }

ne843CopEntryBdr OBJECT-TYPE
SYNTAX      INTEGER {
b300(300),
b1200(1200),
b2400(2400),
b4800(4800),
b9600(9600),
b19200(19200)
}
MAX-ACCESS  read-write
STATUS      current
DESCRIPTION
"Connect Baudrate
Values:
b300(300),
b1200(1200),
b2400(2400),
b4800(4800),
b9600(9600),
b19200(19200)
"
 ::= { ne843CopEntry  6 }

ne843CopEntryDbt OBJECT-TYPE
SYNTAX      INTEGER {
d7(7),
d8(8)
}
MAX-ACCESS  read-write
STATUS      current
DESCRIPTION
"Data Bits
Values:
d7(7),
d8(8)
"
 ::= { ne843CopEntry  7 }

ne843CopEntryPry OBJECT-TYPE
SYNTAX      DisplayString
MAX-ACCESS  read-write
STATUS      current
DESCRIPTION
"Parity
Values:
O,
E,
N
"
 ::= { ne843CopEntry  8 }

ne843CopEntrySbt OBJECT-TYPE
SYNTAX      INTEGER {
s1(1),
s2(2)
}
MAX-ACCESS  read-write
STATUS      current
DESCRIPTION
"Stop Bits
Values:
s1(1),
s2(2)
"
 ::= { ne843CopEntry  9 }

ne843CopEntryDly OBJECT-TYPE
SYNTAX      Integer32(0..9)
MAX-ACCESS  read-write
STATUS      current
DESCRIPTION
"Pager ID Delay"
 ::= { ne843CopEntry  10 }

ne843CopEntryPgr OBJECT-TYPE
SYNTAX      DisplayString
MAX-ACCESS  read-write
STATUS      current
DESCRIPTION
"Pager ID"
 ::= { ne843CopEntry  11 }

ne843CopEntryMsg OBJECT-TYPE
SYNTAX      DisplayString
MAX-ACCESS  read-write
STATUS      current
DESCRIPTION
"Pager Message"
 ::= { ne843CopEntry  12 }



--
-- table COE
--

ne843CoeTable    OBJECT-TYPE
SYNTAX SEQUENCE OF Ne843CoeEntry
MAX-ACCESS not-accessible
STATUS current
DESCRIPTION
        "Table of all Email Address data"
 ::= { ne843  20 }

ne843CoeEntry OBJECT-TYPE
SYNTAX     Ne843CoeEntry
MAX-ACCESS  not-accessible
STATUS      current
DESCRIPTION
       "Entry of information for one Email Address"
INDEX { ne843CoeEntryIndex }
 ::= { ne843CoeTable  1 }

Ne843CoeEntry ::= SEQUENCE {
ne843CoeEntryIndex   INTEGER,
ne843CoeEntryIde   DisplayString,
ne843CoeEntryDes   DisplayString,
ne843CoeEntryAdr   DisplayString,
ne843CoeEntryTyp   DisplayString
}

ne843CoeEntryIndex OBJECT-TYPE
SYNTAX      INTEGER (0..2147483647)
MAX-ACCESS  read-only
STATUS      current
DESCRIPTION
"Table Index"
 ::= { ne843CoeEntry  1 }

ne843CoeEntryIde OBJECT-TYPE
SYNTAX      DisplayString
MAX-ACCESS  read-only
STATUS      current
DESCRIPTION
"Identifier"
 ::= { ne843CoeEntry  2 }

ne843CoeEntryDes OBJECT-TYPE
SYNTAX      DisplayString
MAX-ACCESS  read-write
STATUS      current
DESCRIPTION
"Description"
 ::= { ne843CoeEntry  3 }

ne843CoeEntryAdr OBJECT-TYPE
SYNTAX      DisplayString
MAX-ACCESS  read-write
STATUS      current
DESCRIPTION
"Email Address"
 ::= { ne843CoeEntry  4 }

ne843CoeEntryTyp OBJECT-TYPE
SYNTAX      DisplayString
MAX-ACCESS  read-write
STATUS      current
DESCRIPTION
"Address Type
Values:
NORMAL,
PAGER
"
 ::= { ne843CoeEntry  5 }



--
-- table SND
--

ne843SndTable    OBJECT-TYPE
SYNTAX SEQUENCE OF Ne843SndEntry
MAX-ACCESS not-accessible
STATUS current
DESCRIPTION
        "Table of all SNMP Trap Destination data"
 ::= { ne843  21 }

ne843SndEntry OBJECT-TYPE
SYNTAX     Ne843SndEntry
MAX-ACCESS  not-accessible
STATUS      current
DESCRIPTION
       "Entry of information for one SNMP Trap Destination"
INDEX { ne843SndEntryIndex }
 ::= { ne843SndTable  1 }

Ne843SndEntry ::= SEQUENCE {
ne843SndEntryIndex   INTEGER,
ne843SndEntryIde   DisplayString,
ne843SndEntryDes   DisplayString,
ne843SndEntryIp   DisplayString,
ne843SndEntryCs   DisplayString
}

ne843SndEntryIndex OBJECT-TYPE
SYNTAX      INTEGER (0..2147483647)
MAX-ACCESS  read-only
STATUS      current
DESCRIPTION
"Table Index"
 ::= { ne843SndEntry  1 }

ne843SndEntryIde OBJECT-TYPE
SYNTAX      DisplayString
MAX-ACCESS  read-only
STATUS      current
DESCRIPTION
"Identifier"
 ::= { ne843SndEntry  2 }

ne843SndEntryDes OBJECT-TYPE
SYNTAX      DisplayString
MAX-ACCESS  read-write
STATUS      current
DESCRIPTION
"Description"
 ::= { ne843SndEntry  3 }

ne843SndEntryIp OBJECT-TYPE
SYNTAX      DisplayString
MAX-ACCESS  read-write
STATUS      current
DESCRIPTION
"IP Address"
 ::= { ne843SndEntry  4 }

ne843SndEntryCs OBJECT-TYPE
SYNTAX      DisplayString
MAX-ACCESS  read-write
STATUS      current
DESCRIPTION
"Community String"
 ::= { ne843SndEntry  5 }



--
-- object ne843Po1
--

ne843Po1 OBJECT IDENTIFIER  ::= { ne843  22 }

ne843Po1Ide OBJECT-TYPE
SYNTAX      DisplayString
MAX-ACCESS  read-only
STATUS      current
DESCRIPTION
"Identifier"
 ::= { ne843Po1  1 }

ne843Po1Des OBJECT-TYPE
SYNTAX      DisplayString
MAX-ACCESS  read-write
STATUS      current
DESCRIPTION
"Description"
 ::= { ne843Po1  2 }

ne843Po1Phn OBJECT-TYPE
SYNTAX      DisplayString
MAX-ACCESS  read-write
STATUS      current
DESCRIPTION
"Phone Number"
 ::= { ne843Po1  3 }

ne843Po1Bdr OBJECT-TYPE
SYNTAX      INTEGER {
b300(300),
b1200(1200),
b2400(2400),
b4800(4800),
b9600(9600),
b19200(19200)
}
MAX-ACCESS  read-write
STATUS      current
DESCRIPTION
"Connect Baudrate
Values:
b300(300),
b1200(1200),
b2400(2400),
b4800(4800),
b9600(9600),
b19200(19200)
"
 ::= { ne843Po1  4 }

ne843Po1Dbt OBJECT-TYPE
SYNTAX      INTEGER {
d7(7),
d8(8)
}
MAX-ACCESS  read-write
STATUS      current
DESCRIPTION
"Data Bits
Values:
d7(7),
d8(8)
"
 ::= { ne843Po1  5 }

ne843Po1Pry OBJECT-TYPE
SYNTAX      DisplayString
MAX-ACCESS  read-write
STATUS      current
DESCRIPTION
"Parity
Values:
O,
E,
N
"
 ::= { ne843Po1  6 }

ne843Po1Sbt OBJECT-TYPE
SYNTAX      INTEGER {
s1(1),
s2(2)
}
MAX-ACCESS  read-write
STATUS      current
DESCRIPTION
"Stop Bits
Values:
s1(1),
s2(2)
"
 ::= { ne843Po1  7 }

ne843Po1Int OBJECT-TYPE
SYNTAX      DisplayString
MAX-ACCESS  read-write
STATUS      current
DESCRIPTION
"Interval
Values:
Sunday,
Monday,
Tuesday,
Wednesday,
Thursday,
Friday,
Saturday,
Daily,
Monthly,
Quarterly,
Never
"
 ::= { ne843Po1  8 }

ne843Po1Tim OBJECT-TYPE
SYNTAX      DisplayString
MAX-ACCESS  read-write
STATUS      current
DESCRIPTION
"Time"
 ::= { ne843Po1  9 }

ne843Po1Cl01 OBJECT-TYPE
SYNTAX      DisplayString
MAX-ACCESS  read-write
STATUS      current
DESCRIPTION
"Command Line 1"
 ::= { ne843Po1  10 }

ne843Po1Cl02 OBJECT-TYPE
SYNTAX      DisplayString
MAX-ACCESS  read-write
STATUS      current
DESCRIPTION
"Command Line 2"
 ::= { ne843Po1  11 }

ne843Po1Cl03 OBJECT-TYPE
SYNTAX      DisplayString
MAX-ACCESS  read-write
STATUS      current
DESCRIPTION
"Command Line 3"
 ::= { ne843Po1  12 }

ne843Po1Cl04 OBJECT-TYPE
SYNTAX      DisplayString
MAX-ACCESS  read-write
STATUS      current
DESCRIPTION
"Command Line 4"
 ::= { ne843Po1  13 }

ne843Po1Cl05 OBJECT-TYPE
SYNTAX      DisplayString
MAX-ACCESS  read-write
STATUS      current
DESCRIPTION
"Command Line 5"
 ::= { ne843Po1  14 }

ne843Po1Cl06 OBJECT-TYPE
SYNTAX      DisplayString
MAX-ACCESS  read-write
STATUS      current
DESCRIPTION
"Command Line 6"
 ::= { ne843Po1  15 }

ne843Po1Cl07 OBJECT-TYPE
SYNTAX      DisplayString
MAX-ACCESS  read-write
STATUS      current
DESCRIPTION
"Command Line 7"
 ::= { ne843Po1  16 }

ne843Po1Cl08 OBJECT-TYPE
SYNTAX      DisplayString
MAX-ACCESS  read-write
STATUS      current
DESCRIPTION
"Command Line 8"
 ::= { ne843Po1  17 }

ne843Po1Cl09 OBJECT-TYPE
SYNTAX      DisplayString
MAX-ACCESS  read-write
STATUS      current
DESCRIPTION
"Command Line 9"
 ::= { ne843Po1  18 }

ne843Po1Cl10 OBJECT-TYPE
SYNTAX      DisplayString
MAX-ACCESS  read-write
STATUS      current
DESCRIPTION
"Command Line 10"
 ::= { ne843Po1  19 }

ne843Po1Por OBJECT-TYPE
SYNTAX      DisplayString
MAX-ACCESS  read-only
STATUS      current
DESCRIPTION
"Number Did Not Respond
Value:
Alarm report from POR1
"
 ::= { ne843Po1  20 }


--
-- object ne843Cb1
--

ne843Cb1 OBJECT IDENTIFIER  ::= { ne843  23 }

ne843Cb1Ide OBJECT-TYPE
SYNTAX      DisplayString
MAX-ACCESS  read-only
STATUS      current
DESCRIPTION
"Identifier"
 ::= { ne843Cb1  1 }

ne843Cb1Des OBJECT-TYPE
SYNTAX      DisplayString
MAX-ACCESS  read-write
STATUS      current
DESCRIPTION
"Description"
 ::= { ne843Cb1  2 }

ne843Cb1Stt OBJECT-TYPE
SYNTAX      INTEGER {
off(0),
on(1)
}
MAX-ACCESS  read-write
STATUS      current
DESCRIPTION
"State
Values:
off(0),
on(1)
"
 ::= { ne843Cb1  3 }

ne843Cb1Ph1 OBJECT-TYPE
SYNTAX      DisplayString
MAX-ACCESS  read-write
STATUS      current
DESCRIPTION
"Call-Back Phone Number 1"
 ::= { ne843Cb1  4 }

ne843Cb1Br1 OBJECT-TYPE
SYNTAX      INTEGER {
b300(300),
b1200(1200),
b2400(2400),
b4800(4800),
b9600(9600),
b19200(19200)
}
MAX-ACCESS  read-write
STATUS      current
DESCRIPTION
"Connect Baudrate 1
Values:
b300(300),
b1200(1200),
b2400(2400),
b4800(4800),
b9600(9600),
b19200(19200)
"
 ::= { ne843Cb1  5 }

ne843Cb1Ph2 OBJECT-TYPE
SYNTAX      DisplayString
MAX-ACCESS  read-write
STATUS      current
DESCRIPTION
"Call-Back Phone Number 2"
 ::= { ne843Cb1  6 }

ne843Cb1Br2 OBJECT-TYPE
SYNTAX      INTEGER {
b300(300),
b1200(1200),
b2400(2400),
b4800(4800),
b9600(9600),
b19200(19200)
}
MAX-ACCESS  read-write
STATUS      current
DESCRIPTION
"Connect Baudrate 2
Values:
b300(300),
b1200(1200),
b2400(2400),
b4800(4800),
b9600(9600),
b19200(19200)
"
 ::= { ne843Cb1  7 }

ne843Cb1Ph3 OBJECT-TYPE
SYNTAX      DisplayString
MAX-ACCESS  read-write
STATUS      current
DESCRIPTION
"Call-Back Phone Number 3"
 ::= { ne843Cb1  8 }

ne843Cb1Br3 OBJECT-TYPE
SYNTAX      INTEGER {
b300(300),
b1200(1200),
b2400(2400),
b4800(4800),
b9600(9600),
b19200(19200)
}
MAX-ACCESS  read-write
STATUS      current
DESCRIPTION
"Connect Baudrate 3
Values:
b300(300),
b1200(1200),
b2400(2400),
b4800(4800),
b9600(9600),
b19200(19200)
"
 ::= { ne843Cb1  9 }

ne843Cb1Ph4 OBJECT-TYPE
SYNTAX      DisplayString
MAX-ACCESS  read-write
STATUS      current
DESCRIPTION
"Call-Back Phone Number 4"
 ::= { ne843Cb1  10 }

ne843Cb1Br4 OBJECT-TYPE
SYNTAX      INTEGER {
b300(300),
b1200(1200),
b2400(2400),
b4800(4800),
b9600(9600),
b19200(19200)
}
MAX-ACCESS  read-write
STATUS      current
DESCRIPTION
"Connect Baudrate 4
Values:
b300(300),
b1200(1200),
b2400(2400),
b4800(4800),
b9600(9600),
b19200(19200)
"
 ::= { ne843Cb1  11 }

ne843Cb1Ph5 OBJECT-TYPE
SYNTAX      DisplayString
MAX-ACCESS  read-write
STATUS      current
DESCRIPTION
"Call-Back Phone Number 5"
 ::= { ne843Cb1  12 }

ne843Cb1Br5 OBJECT-TYPE
SYNTAX      INTEGER {
b300(300),
b1200(1200),
b2400(2400),
b4800(4800),
b9600(9600),
b19200(19200)
}
MAX-ACCESS  read-write
STATUS      current
DESCRIPTION
"Connect Baudrate 5
Values:
b300(300),
b1200(1200),
b2400(2400),
b4800(4800),
b9600(9600),
b19200(19200)
"
 ::= { ne843Cb1  13 }


--
-- object ne843Mp1
--

ne843Mp1 OBJECT IDENTIFIER  ::= { ne843  24 }

ne843Mp1Ide OBJECT-TYPE
SYNTAX      DisplayString
MAX-ACCESS  read-only
STATUS      current
DESCRIPTION
"Identifier"
 ::= { ne843Mp1  1 }

ne843Mp1Des OBJECT-TYPE
SYNTAX      DisplayString
MAX-ACCESS  read-write
STATUS      current
DESCRIPTION
"Description"
 ::= { ne843Mp1  2 }

ne843Mp1Stt OBJECT-TYPE
SYNTAX      DisplayString
MAX-ACCESS  read-only
STATUS      current
DESCRIPTION
"State"
 ::= { ne843Mp1  3 }

ne843Mp1Bdr OBJECT-TYPE
SYNTAX      INTEGER {
b300(300),
b1200(1200),
b2400(2400),
b4800(4800),
b9600(9600),
b19200(19200)
}
MAX-ACCESS  read-write
STATUS      current
DESCRIPTION
"Baudrate
Values:
b300(300),
b1200(1200),
b2400(2400),
b4800(4800),
b9600(9600),
b19200(19200)
"
 ::= { ne843Mp1  4 }

ne843Mp1Dbt OBJECT-TYPE
SYNTAX      INTEGER {
d7(7),
d8(8)
}
MAX-ACCESS  read-write
STATUS      current
DESCRIPTION
"Data Bits
Values:
d7(7),
d8(8)
"
 ::= { ne843Mp1  5 }

ne843Mp1Pry OBJECT-TYPE
SYNTAX      DisplayString
MAX-ACCESS  read-write
STATUS      current
DESCRIPTION
"Parity
Values:
O,
E,
N
"
 ::= { ne843Mp1  6 }

ne843Mp1Sbt OBJECT-TYPE
SYNTAX      INTEGER {
s1(1),
s2(2)
}
MAX-ACCESS  read-write
STATUS      current
DESCRIPTION
"Stop Bits
Values:
s1(1),
s2(2)
"
 ::= { ne843Mp1  7 }

ne843Mp1Tmo OBJECT-TYPE
SYNTAX      Integer32(0..45)
MAX-ACCESS  read-write
STATUS      current
DESCRIPTION
"Time-Out"
 ::= { ne843Mp1  8 }

ne843Mp1Hsh OBJECT-TYPE
SYNTAX      DisplayString
MAX-ACCESS  read-write
STATUS      current
DESCRIPTION
"Handshaking
Values:
NO,
SW
"
 ::= { ne843Mp1  9 }

ne843Mp1Nrg OBJECT-TYPE
SYNTAX      Integer32(2..15)
MAX-ACCESS  read-write
STATUS      current
DESCRIPTION
"Number of Rings Before Answer"
 ::= { ne843Mp1  10 }

ne843Mp1Wre OBJECT-TYPE
SYNTAX      INTEGER {
disable(0),
enable(1)
}
MAX-ACCESS  read-write
STATUS      current
DESCRIPTION
"Write Enable
Values:
disable(0),
enable(1)
"
 ::= { ne843Mp1  11 }

ne843Mp1Ins OBJECT-TYPE
SYNTAX      DisplayString
MAX-ACCESS  read-write
STATUS      current
DESCRIPTION
"Modem Init String"
 ::= { ne843Mp1  12 }


--
-- object ne843Lp1
--

ne843Lp1 OBJECT IDENTIFIER  ::= { ne843  25 }

ne843Lp1Ide OBJECT-TYPE
SYNTAX      DisplayString
MAX-ACCESS  read-only
STATUS      current
DESCRIPTION
"Identifier"
 ::= { ne843Lp1  1 }

ne843Lp1Des OBJECT-TYPE
SYNTAX      DisplayString
MAX-ACCESS  read-write
STATUS      current
DESCRIPTION
"Description"
 ::= { ne843Lp1  2 }

ne843Lp1Stt OBJECT-TYPE
SYNTAX      DisplayString
MAX-ACCESS  read-only
STATUS      current
DESCRIPTION
"State"
 ::= { ne843Lp1  3 }

ne843Lp1Bdr OBJECT-TYPE
SYNTAX      INTEGER {
b300(300),
b1200(1200),
b2400(2400),
b4800(4800),
b9600(9600),
b19200(19200)
}
MAX-ACCESS  read-write
STATUS      current
DESCRIPTION
"Baudrate
Values:
b300(300),
b1200(1200),
b2400(2400),
b4800(4800),
b9600(9600),
b19200(19200)
"
 ::= { ne843Lp1  4 }

ne843Lp1Dbt OBJECT-TYPE
SYNTAX      INTEGER {
d7(7),
d8(8)
}
MAX-ACCESS  read-write
STATUS      current
DESCRIPTION
"Data Bits
Values:
d7(7),
d8(8)
"
 ::= { ne843Lp1  5 }

ne843Lp1Pry OBJECT-TYPE
SYNTAX      DisplayString
MAX-ACCESS  read-write
STATUS      current
DESCRIPTION
"Parity
Values:
O,
E,
N
"
 ::= { ne843Lp1  6 }

ne843Lp1Sbt OBJECT-TYPE
SYNTAX      INTEGER {
s1(1),
s2(2)
}
MAX-ACCESS  read-write
STATUS      current
DESCRIPTION
"Stop Bits
Values:
s1(1),
s2(2)
"
 ::= { ne843Lp1  7 }

ne843Lp1Tmo OBJECT-TYPE
SYNTAX      Integer32(0..45)
MAX-ACCESS  read-write
STATUS      current
DESCRIPTION
"Time-Out"
 ::= { ne843Lp1  8 }

ne843Lp1Hsh OBJECT-TYPE
SYNTAX      DisplayString
MAX-ACCESS  read-write
STATUS      current
DESCRIPTION
"Handshaking
Values:
NO,
HW,
SW
"
 ::= { ne843Lp1  9 }

ne843Lp1App OBJECT-TYPE
SYNTAX      DisplayString
MAX-ACCESS  read-write
STATUS      current
DESCRIPTION
"Application
Values:
TERMINAL,
EVENT LOG
"
 ::= { ne843Lp1  10 }

ne843Lp1Wre OBJECT-TYPE
SYNTAX      INTEGER {
disable(0),
enable(1)
}
MAX-ACCESS  read-write
STATUS      current
DESCRIPTION
"Write Enable
Values:
disable(0),
enable(1)
"
 ::= { ne843Lp1  11 }


--
-- object ne843Tlm1
--

ne843Tlm1 OBJECT IDENTIFIER  ::= { ne843  26 }

ne843Tlm1Ide OBJECT-TYPE
SYNTAX      DisplayString
MAX-ACCESS  read-only
STATUS      current
DESCRIPTION
"Identifier"
 ::= { ne843Tlm1  1 }

ne843Tlm1Des OBJECT-TYPE
SYNTAX      DisplayString
MAX-ACCESS  read-write
STATUS      current
DESCRIPTION
"Description"
 ::= { ne843Tlm1  2 }

ne843Tlm1Aue OBJECT-TYPE
SYNTAX      INTEGER {
disable(0),
enable(1)
}
MAX-ACCESS  read-write
STATUS      current
DESCRIPTION
"Activate-User Enable
Values:
disable(0),
enable(1)
"
 ::= { ne843Tlm1  3 }

ne843Tlm1Prt OBJECT-TYPE
SYNTAX      Integer32
MAX-ACCESS  read-write
STATUS      current
DESCRIPTION
"TCP/IP Port"
 ::= { ne843Tlm1  4 }

ne843Tlm1Tmo OBJECT-TYPE
SYNTAX      Integer32(0..60)
UNITS       "Minutes"
MAX-ACCESS  read-write
STATUS      current
DESCRIPTION
"Timeout (Minutes)"
 ::= { ne843Tlm1  5 }


--
-- table TL1
--

ne843Tl1Table    OBJECT-TYPE
SYNTAX SEQUENCE OF Ne843Tl1Entry
MAX-ACCESS not-accessible
STATUS current
DESCRIPTION
        "Table of all TL1 Object data"
 ::= { ne843  27 }

ne843Tl1Entry OBJECT-TYPE
SYNTAX     Ne843Tl1Entry
MAX-ACCESS  not-accessible
STATUS      current
DESCRIPTION
       "Entry of information for one TL1 Object"
INDEX { ne843Tl1EntryIndex }
 ::= { ne843Tl1Table  1 }

Ne843Tl1Entry ::= SEQUENCE {
ne843Tl1EntryIndex   INTEGER,
ne843Tl1EntryIde   DisplayString,
ne843Tl1EntryDes   DisplayString,
ne843Tl1EntryCds   DisplayString,
ne843Tl1EntryAid   DisplayString,
ne843Tl1EntryCnd   DisplayString,
ne843Tl1EntrySaf   INTEGER,
ne843Tl1EntryRpt   DisplayString
}

ne843Tl1EntryIndex OBJECT-TYPE
SYNTAX      INTEGER (0..2147483647)
MAX-ACCESS  read-only
STATUS      current
DESCRIPTION
"Table Index"
 ::= { ne843Tl1Entry  1 }

ne843Tl1EntryIde OBJECT-TYPE
SYNTAX      DisplayString
MAX-ACCESS  read-only
STATUS      current
DESCRIPTION
"Identifier"
 ::= { ne843Tl1Entry  2 }

ne843Tl1EntryDes OBJECT-TYPE
SYNTAX      DisplayString
MAX-ACCESS  read-write
STATUS      current
DESCRIPTION
"Description"
 ::= { ne843Tl1Entry  3 }

ne843Tl1EntryCds OBJECT-TYPE
SYNTAX      DisplayString
MAX-ACCESS  read-write
STATUS      current
DESCRIPTION
"Condition Description"
 ::= { ne843Tl1Entry  4 }

ne843Tl1EntryAid OBJECT-TYPE
SYNTAX      DisplayString
MAX-ACCESS  read-write
STATUS      current
DESCRIPTION
"Aid"
 ::= { ne843Tl1Entry  5 }

ne843Tl1EntryCnd OBJECT-TYPE
SYNTAX      DisplayString
MAX-ACCESS  read-write
STATUS      current
DESCRIPTION
"Condition Type"
 ::= { ne843Tl1Entry  6 }

ne843Tl1EntrySaf OBJECT-TYPE
SYNTAX      INTEGER {
no(0),
yes(1)
}
MAX-ACCESS  read-write
STATUS      current
DESCRIPTION
"Service Affecting
Values:
no(0),
yes(1)
"
 ::= { ne843Tl1Entry  7 }

ne843Tl1EntryRpt OBJECT-TYPE
SYNTAX      DisplayString
MAX-ACCESS  read-write
STATUS      current
DESCRIPTION
"Reporting
Values:
EQUIPMENT,
ENVIRONMENT,
PRESENCE
"
 ::= { ne843Tl1Entry  8 }



--
-- object ne843Net1
--

ne843Net1 OBJECT IDENTIFIER  ::= { ne843  28 }

ne843Net1Ide OBJECT-TYPE
SYNTAX      DisplayString
MAX-ACCESS  read-only
STATUS      current
DESCRIPTION
"Identifier"
 ::= { ne843Net1  1 }

ne843Net1Des OBJECT-TYPE
SYNTAX      DisplayString
MAX-ACCESS  read-write
STATUS      current
DESCRIPTION
"Description"
 ::= { ne843Net1  2 }

ne843Net1Ead OBJECT-TYPE
SYNTAX      DisplayString
MAX-ACCESS  read-only
STATUS      current
DESCRIPTION
"Ethernet Address"
 ::= { ne843Net1  3 }

ne843Net1Dhcp OBJECT-TYPE
SYNTAX      INTEGER {
static(0),
dhcpClient(1),
dhcpServer(2)
}
MAX-ACCESS  read-write
STATUS      current
DESCRIPTION
"IP Addressing Mode
Values:
static(0),
dhcpClient(1),
dhcpServer(2)
"
 ::= { ne843Net1  4 }

ne843Net1Ip OBJECT-TYPE
SYNTAX      DisplayString
MAX-ACCESS  read-write
STATUS      current
DESCRIPTION
"Static IPv4 Address"
 ::= { ne843Net1  5 }

ne843Net1Wip OBJECT-TYPE
SYNTAX      DisplayString
MAX-ACCESS  read-only
STATUS      current
DESCRIPTION
"Working IPv4 Address"
 ::= { ne843Net1  6 }

ne843Net1Sub OBJECT-TYPE
SYNTAX      DisplayString
MAX-ACCESS  read-write
STATUS      current
DESCRIPTION
"Subnet Mask"
 ::= { ne843Net1  7 }

ne843Net1Gtwy OBJECT-TYPE
SYNTAX      DisplayString
MAX-ACCESS  read-write
STATUS      current
DESCRIPTION
"Default Gateway"
 ::= { ne843Net1  8 }

ne843Net1Host OBJECT-TYPE
SYNTAX      DisplayString
MAX-ACCESS  read-write
STATUS      current
DESCRIPTION
"Host Name"
 ::= { ne843Net1  9 }

ne843Net1Dom OBJECT-TYPE
SYNTAX      DisplayString
MAX-ACCESS  read-write
STATUS      current
DESCRIPTION
"Domain Name"
 ::= { ne843Net1  10 }

ne843Net1Dns OBJECT-TYPE
SYNTAX      DisplayString
MAX-ACCESS  read-write
STATUS      current
DESCRIPTION
"DNS Server Address"
 ::= { ne843Net1  11 }

ne843Net1Wre OBJECT-TYPE
SYNTAX      INTEGER {
disable(0),
enable(1)
}
MAX-ACCESS  read-write
STATUS      current
DESCRIPTION
"Write Enable
Values:
disable(0),
enable(1)
"
 ::= { ne843Net1  12 }

ne843Net1Tmo OBJECT-TYPE
SYNTAX      Integer32(0..1440)
UNITS       "Minutes"
MAX-ACCESS  read-write
STATUS      current
DESCRIPTION
"Timeout (Minutes)"
 ::= { ne843Net1  13 }

ne843Net1Msrv OBJECT-TYPE
SYNTAX      DisplayString
MAX-ACCESS  read-write
STATUS      current
DESCRIPTION
"Mail Server Address"
 ::= { ne843Net1  14 }

ne843Net1Ntp OBJECT-TYPE
SYNTAX      DisplayString
MAX-ACCESS  read-write
STATUS      current
DESCRIPTION
"Time Server Address"
 ::= { ne843Net1  15 }

ne843Net1Sma OBJECT-TYPE
SYNTAX      DisplayString
MAX-ACCESS  read-write
STATUS      current
DESCRIPTION
"Send Email As"
 ::= { ne843Net1  16 }

ne843Net1Sid OBJECT-TYPE
SYNTAX      DisplayString
MAX-ACCESS  read-only
STATUS      current
DESCRIPTION
"SNMP Engine ID"
 ::= { ne843Net1  17 }

ne843Net1Fpe OBJECT-TYPE
SYNTAX      INTEGER {
disable(0),
enable(1)
}
MAX-ACCESS  read-write
STATUS      current
DESCRIPTION
"FTP Access Enable
Values:
disable(0),
enable(1)
"
 ::= { ne843Net1  18 }

ne843Net1Hpe OBJECT-TYPE
SYNTAX      INTEGER {
disable(0),
enable(1)
}
MAX-ACCESS  read-write
STATUS      current
DESCRIPTION
"HTTP Web Access Enable
Values:
disable(0),
enable(1)
"
 ::= { ne843Net1  19 }

ne843Net1Hse OBJECT-TYPE
SYNTAX      INTEGER {
disable(0),
enable(1)
}
MAX-ACCESS  read-write
STATUS      current
DESCRIPTION
"HTTPS Web Access Enable
Values:
disable(0),
enable(1)
"
 ::= { ne843Net1  20 }

ne843Net1She OBJECT-TYPE
SYNTAX      INTEGER {
disable(0),
enable(1)
}
MAX-ACCESS  read-write
STATUS      current
DESCRIPTION
"SSH Access Enable
Values:
disable(0),
enable(1)
"
 ::= { ne843Net1  21 }

ne843Net1Sne OBJECT-TYPE
SYNTAX      INTEGER {
disable(0),
enable(1)
}
MAX-ACCESS  read-write
STATUS      current
DESCRIPTION
"SNMP Access Enable
Values:
disable(0),
enable(1)
"
 ::= { ne843Net1  22 }

ne843Net1Tle OBJECT-TYPE
SYNTAX      INTEGER {
disable(0),
enable(1)
}
MAX-ACCESS  read-write
STATUS      current
DESCRIPTION
"Telnet Access Enable
Values:
disable(0),
enable(1)
"
 ::= { ne843Net1  23 }

ne843Net1Ip6 OBJECT-TYPE
SYNTAX      DisplayString
MAX-ACCESS  read-write
STATUS      current
DESCRIPTION
"Static IPv6 Address"
 ::= { ne843Net1  24 }

ne843Net1Gtwy6 OBJECT-TYPE
SYNTAX      DisplayString
MAX-ACCESS  read-write
STATUS      current
DESCRIPTION
"Static IPv6 Gateway/Router"
 ::= { ne843Net1  25 }

ne843Net1Wip6 OBJECT-TYPE
SYNTAX      DisplayString
MAX-ACCESS  read-only
STATUS      current
DESCRIPTION
"Working IPv6 Address"
 ::= { ne843Net1  26 }

ne843Net1Ll6 OBJECT-TYPE
SYNTAX      DisplayString
MAX-ACCESS  read-only
STATUS      current
DESCRIPTION
"Working IPv6 Link Local Address"
 ::= { ne843Net1  27 }

ne843Net1Pl6 OBJECT-TYPE
SYNTAX      Integer32(1..127)
MAX-ACCESS  read-write
STATUS      current
DESCRIPTION
"IPv6 Prefix Length"
 ::= { ne843Net1  28 }

ne843Net1Wgtwy6 OBJECT-TYPE
SYNTAX      DisplayString
MAX-ACCESS  read-only
STATUS      current
DESCRIPTION
"Working IPv6 Gateway/Router Address"
 ::= { ne843Net1  29 }


--
-- table DRC
--

ne843DrcTable    OBJECT-TYPE
SYNTAX SEQUENCE OF Ne843DrcEntry
MAX-ACCESS not-accessible
STATUS current
DESCRIPTION
        "Table of all Derived Channel data"
 ::= { ne843  29 }

ne843DrcEntry OBJECT-TYPE
SYNTAX     Ne843DrcEntry
MAX-ACCESS  not-accessible
STATUS      current
DESCRIPTION
       "Entry of information for one Derived Channel"
INDEX { ne843DrcEntryIndex }
 ::= { ne843DrcTable  1 }

Ne843DrcEntry ::= SEQUENCE {
ne843DrcEntryIndex   INTEGER,
ne843DrcEntryIde   DisplayString,
ne843DrcEntryDes   DisplayString,
ne843DrcEntryVal   DisplayString,
ne843DrcEntryPrg   DisplayString,
ne843DrcEntryUni   DisplayString
}

ne843DrcEntryIndex OBJECT-TYPE
SYNTAX      INTEGER (0..2147483647)
MAX-ACCESS  read-only
STATUS      current
DESCRIPTION
"Table Index"
 ::= { ne843DrcEntry  1 }

ne843DrcEntryIde OBJECT-TYPE
SYNTAX      DisplayString
MAX-ACCESS  read-only
STATUS      current
DESCRIPTION
"Identifier"
 ::= { ne843DrcEntry  2 }

ne843DrcEntryDes OBJECT-TYPE
SYNTAX      DisplayString
MAX-ACCESS  read-write
STATUS      current
DESCRIPTION
"Description"
 ::= { ne843DrcEntry  3 }

ne843DrcEntryVal OBJECT-TYPE
SYNTAX      DisplayString
MAX-ACCESS  read-only
STATUS      current
DESCRIPTION
"Value"
 ::= { ne843DrcEntry  4 }

ne843DrcEntryPrg OBJECT-TYPE
SYNTAX      DisplayString
MAX-ACCESS  read-write
STATUS      current
DESCRIPTION
"Program Line"
 ::= { ne843DrcEntry  5 }

ne843DrcEntryUni OBJECT-TYPE
SYNTAX      DisplayString
MAX-ACCESS  read-write
STATUS      current
DESCRIPTION
"Unit"
 ::= { ne843DrcEntry  6 }



--
-- table INP
--

ne843InpTable    OBJECT-TYPE
SYNTAX SEQUENCE OF Ne843InpEntry
MAX-ACCESS not-accessible
STATUS current
DESCRIPTION
        "Table of all Input Management data"
 ::= { ne843  30 }

ne843InpEntry OBJECT-TYPE
SYNTAX     Ne843InpEntry
MAX-ACCESS  not-accessible
STATUS      current
DESCRIPTION
       "Entry of information for one Input Management"
INDEX { ne843InpEntryIndex }
 ::= { ne843InpTable  1 }

Ne843InpEntry ::= SEQUENCE {
ne843InpEntryIndex   INTEGER,
ne843InpEntryIde   DisplayString,
ne843InpEntryDes   DisplayString,
ne843InpEntryStt   INTEGER,
ne843InpEntryTyp   DisplayString,
ne843InpEntryPol   DisplayString,
ne843InpEntrySn   DisplayString,
ne843InpEntryBrc   DisplayString
}

ne843InpEntryIndex OBJECT-TYPE
SYNTAX      INTEGER (0..2147483647)
MAX-ACCESS  read-only
STATUS      current
DESCRIPTION
"Table Index"
 ::= { ne843InpEntry  1 }

ne843InpEntryIde OBJECT-TYPE
SYNTAX      DisplayString
MAX-ACCESS  read-only
STATUS      current
DESCRIPTION
"Identifier"
 ::= { ne843InpEntry  2 }

ne843InpEntryDes OBJECT-TYPE
SYNTAX      DisplayString
MAX-ACCESS  read-write
STATUS      current
DESCRIPTION
"Description"
 ::= { ne843InpEntry  3 }

ne843InpEntryStt OBJECT-TYPE
SYNTAX      INTEGER {
alarming(1),
nonAlarming(0)
}
MAX-ACCESS  read-only
STATUS      current
DESCRIPTION
"Input State
Values:
alarming(1),
nonAlarming(0)
"
 ::= { ne843InpEntry  4 }

ne843InpEntryTyp OBJECT-TYPE
SYNTAX      DisplayString
MAX-ACCESS  read-write
STATUS      current
DESCRIPTION
"Type Alarm Object ID or, REMLVD for Remote LVD"
 ::= { ne843InpEntry  5 }

ne843InpEntryPol OBJECT-TYPE
SYNTAX      DisplayString
MAX-ACCESS  read-write
STATUS      current
DESCRIPTION
"Input Alarming Polarity
Values:
OPEN,
CLOSED
"
 ::= { ne843InpEntry  6 }

ne843InpEntrySn OBJECT-TYPE
SYNTAX      DisplayString
MAX-ACCESS  read-only
STATUS      current
DESCRIPTION
"Serial Number"
 ::= { ne843InpEntry  7 }

ne843InpEntryBrc OBJECT-TYPE
SYNTAX      DisplayString
MAX-ACCESS  read-only
STATUS      current
DESCRIPTION
"Board Code"
 ::= { ne843InpEntry  8 }



--
-- table MSV
--

ne843MsvTable    OBJECT-TYPE
SYNTAX SEQUENCE OF Ne843MsvEntry
MAX-ACCESS not-accessible
STATUS current
DESCRIPTION
        "Table of all Midstring Voltage Monitor data"
 ::= { ne843  31 }

ne843MsvEntry OBJECT-TYPE
SYNTAX     Ne843MsvEntry
MAX-ACCESS  not-accessible
STATUS      current
DESCRIPTION
       "Entry of information for one Midstring Voltage Monitor"
INDEX { ne843MsvEntryIndex }
 ::= { ne843MsvTable  1 }

Ne843MsvEntry ::= SEQUENCE {
ne843MsvEntryIndex   INTEGER,
ne843MsvEntryIde   DisplayString,
ne843MsvEntryDes   DisplayString,
ne843MsvEntryStt   DisplayString,
ne843MsvEntryVal   Integer32,
ne843MsvEntryDid   DisplayString,
ne843MsvEntryDid1   INTEGER
}

ne843MsvEntryIndex OBJECT-TYPE
SYNTAX      INTEGER (0..2147483647)
MAX-ACCESS  read-only
STATUS      current
DESCRIPTION
"Table Index"
 ::= { ne843MsvEntry  1 }

ne843MsvEntryIde OBJECT-TYPE
SYNTAX      DisplayString
MAX-ACCESS  read-only
STATUS      current
DESCRIPTION
"Identifier"
 ::= { ne843MsvEntry  2 }

ne843MsvEntryDes OBJECT-TYPE
SYNTAX      DisplayString
MAX-ACCESS  read-write
STATUS      current
DESCRIPTION
"Description"
 ::= { ne843MsvEntry  3 }

ne843MsvEntryStt OBJECT-TYPE
SYNTAX      DisplayString
MAX-ACCESS  read-only
STATUS      current
DESCRIPTION
"State"
 ::= { ne843MsvEntry  4 }

ne843MsvEntryVal OBJECT-TYPE
SYNTAX      Integer32
UNITS       "mV"
MAX-ACCESS  read-only
STATUS      current
DESCRIPTION
"Value (mV)"
 ::= { ne843MsvEntry  5 }

ne843MsvEntryDid OBJECT-TYPE
SYNTAX      DisplayString
MAX-ACCESS  read-only
STATUS      current
DESCRIPTION
"Duplicate ID"
 ::= { ne843MsvEntry  6 }

ne843MsvEntryDid1 OBJECT-TYPE
SYNTAX      INTEGER {
inactive(0),
active(1)
}
MAX-ACCESS  read-only
STATUS      current
DESCRIPTION
"Duplicate ID
Values:
inactive(0),
active(1)
"
 ::= { ne843MsvEntry  7 }



--
-- object ne843Rp1
--

ne843Rp1 OBJECT IDENTIFIER  ::= { ne843  32 }

ne843Rp1Ide OBJECT-TYPE
SYNTAX      DisplayString
MAX-ACCESS  read-only
STATUS      current
DESCRIPTION
"Identifier"
 ::= { ne843Rp1  1 }

ne843Rp1Des OBJECT-TYPE
SYNTAX      DisplayString
MAX-ACCESS  read-write
STATUS      current
DESCRIPTION
"Description"
 ::= { ne843Rp1  2 }

ne843Rp1Frq OBJECT-TYPE
SYNTAX      Integer32(15..50)
UNITS       "Hz"
MAX-ACCESS  read-write
STATUS      current
DESCRIPTION
"Frequency (Hz)"
 ::= { ne843Rp1  3 }

ne843Rp1Vsp OBJECT-TYPE
SYNTAX      Integer32(65..100)
UNITS       "Volts"
MAX-ACCESS  read-write
STATUS      current
DESCRIPTION
"Voltage Set-point (Volts)"
 ::= { ne843Rp1  4 }

ne843Rp1Ofe OBJECT-TYPE
SYNTAX      INTEGER {
disable(0),
enable(1)
}
MAX-ACCESS  read-write
STATUS      current
DESCRIPTION
"Offset
Values:
disable(0),
enable(1)
"
 ::= { ne843Rp1  5 }

ne843Rp1Rme OBJECT-TYPE
SYNTAX      INTEGER {
disable(0),
enable(1)
}
MAX-ACCESS  read-write
STATUS      current
DESCRIPTION
"Redundancy Monitor
Values:
disable(0),
enable(1)
"
 ::= { ne843Rp1  6 }

ne843Rp1Rss OBJECT-TYPE
SYNTAX      INTEGER {
restart(1)
}
MAX-ACCESS  read-write
STATUS      current
DESCRIPTION
"Restart
Values:
restart(1)
"
 ::= { ne843Rp1  7 }

ne843Rp1Rf OBJECT-TYPE
SYNTAX      DisplayString
MAX-ACCESS  read-only
STATUS      current
DESCRIPTION
"Ringer Minor Fail
Value:
Alarm report from RFN1
"
 ::= { ne843Rp1  8 }

ne843Rp1Rpff OBJECT-TYPE
SYNTAX      DisplayString
MAX-ACCESS  read-only
STATUS      current
DESCRIPTION
"Ringer Fan Fail
Value:
Alarm report from RPFF1
"
 ::= { ne843Rp1  9 }

ne843Rp1Rprl OBJECT-TYPE
SYNTAX      DisplayString
MAX-ACCESS  read-only
STATUS      current
DESCRIPTION
"Ringer Redundancy Loss
Value:
Alarm report from RPRL1
"
 ::= { ne843Rp1  10 }

ne843Rp1Rpfj OBJECT-TYPE
SYNTAX      DisplayString
MAX-ACCESS  read-only
STATUS      current
DESCRIPTION
"Ringer Major Fail
Value:
Alarm report from RPFJ1
"
 ::= { ne843Rp1  11 }

ne843Rp1Rpxj OBJECT-TYPE
SYNTAX      DisplayString
MAX-ACCESS  read-only
STATUS      current
DESCRIPTION
"Ringer Major External Fault
Value:
Alarm report from RPXJ1
"
 ::= { ne843Rp1  12 }

ne843Rp1Rpxn OBJECT-TYPE
SYNTAX      DisplayString
MAX-ACCESS  read-only
STATUS      current
DESCRIPTION
"Ringer Minor External Fault
Value:
Alarm report from RPXN1
"
 ::= { ne843Rp1  13 }

ne843Rp1Rcdp OBJECT-TYPE
SYNTAX      DisplayString
MAX-ACCESS  read-only
STATUS      current
DESCRIPTION
"Ringer ID Conflict
Value:
Alarm report from RCDP1
"
 ::= { ne843Rp1  14 }

ne843Rp1Cap OBJECT-TYPE
SYNTAX      Integer32
UNITS       "VA"
MAX-ACCESS  read-only
STATUS      current
DESCRIPTION
"Capacity (VA)"
 ::= { ne843Rp1  15 }

ne843Rp1Olcap OBJECT-TYPE
SYNTAX      Integer32
UNITS       "VA"
MAX-ACCESS  read-only
STATUS      current
DESCRIPTION
"On Line Capacity (VA)"
 ::= { ne843Rp1  16 }

ne843Rp1Va OBJECT-TYPE
SYNTAX      Integer32
UNITS       "VA"
MAX-ACCESS  read-only
STATUS      current
DESCRIPTION
"Total (VA)"
 ::= { ne843Rp1  17 }

ne843Rp1Rrf OBJECT-TYPE
SYNTAX      INTEGER {
disable(0),
enable(1)
}
MAX-ACCESS  read-write
STATUS      current
DESCRIPTION
"Standby Enable
Values:
disable(0),
enable(1)
"
 ::= { ne843Rp1  18 }


--
-- table RCH
--

ne843RchTable    OBJECT-TYPE
SYNTAX SEQUENCE OF Ne843RchEntry
MAX-ACCESS not-accessible
STATUS current
DESCRIPTION
        "Table of all Ringer Chassis data"
 ::= { ne843  33 }

ne843RchEntry OBJECT-TYPE
SYNTAX     Ne843RchEntry
MAX-ACCESS  not-accessible
STATUS      current
DESCRIPTION
       "Entry of information for one Ringer Chassis"
INDEX { ne843RchEntryIndex }
 ::= { ne843RchTable  1 }

Ne843RchEntry ::= SEQUENCE {
ne843RchEntryIndex   INTEGER,
ne843RchEntryIde   DisplayString,
ne843RchEntryDes   DisplayString,
ne843RchEntryStt   DisplayString,
ne843RchEntryVa   Integer32,
ne843RchEntryPri   DisplayString,
ne843RchEntrySec   DisplayString,
ne843RchEntryRf   INTEGER,
ne843RchEntryRpff   INTEGER,
ne843RchEntryRpxj   INTEGER,
ne843RchEntryRpxn   INTEGER,
ne843RchEntryRprl   INTEGER,
ne843RchEntryRpfj   INTEGER,
ne843RchEntryRcdp   INTEGER,
ne843RchEntryPsn   DisplayString,
ne843RchEntryPtyp   DisplayString,
ne843RchEntryPstt   DisplayString,
ne843RchEntrySsn   DisplayString,
ne843RchEntryStyp   DisplayString,
ne843RchEntrySstt   DisplayString,
ne843RchEntryCap   Integer32
}

ne843RchEntryIndex OBJECT-TYPE
SYNTAX      INTEGER (0..2147483647)
MAX-ACCESS  read-only
STATUS      current
DESCRIPTION
"Table Index"
 ::= { ne843RchEntry  1 }

ne843RchEntryIde OBJECT-TYPE
SYNTAX      DisplayString
MAX-ACCESS  read-only
STATUS      current
DESCRIPTION
"Identifier"
 ::= { ne843RchEntry  2 }

ne843RchEntryDes OBJECT-TYPE
SYNTAX      DisplayString
MAX-ACCESS  read-write
STATUS      current
DESCRIPTION
"Description"
 ::= { ne843RchEntry  3 }

ne843RchEntryStt OBJECT-TYPE
SYNTAX      DisplayString
MAX-ACCESS  read-write
STATUS      current
DESCRIPTION
"Ringer Group State"
 ::= { ne843RchEntry  4 }

ne843RchEntryVa OBJECT-TYPE
SYNTAX      Integer32
UNITS       "mVA"
MAX-ACCESS  read-only
STATUS      current
DESCRIPTION
"Ringer Output (mVA)"
 ::= { ne843RchEntry  5 }

ne843RchEntryPri OBJECT-TYPE
SYNTAX      DisplayString
MAX-ACCESS  read-only
STATUS      current
DESCRIPTION
"Primary Ringer"
 ::= { ne843RchEntry  6 }

ne843RchEntrySec OBJECT-TYPE
SYNTAX      DisplayString
MAX-ACCESS  read-only
STATUS      current
DESCRIPTION
"Secondary Ringer"
 ::= { ne843RchEntry  7 }

ne843RchEntryRf OBJECT-TYPE
SYNTAX      INTEGER {
inactive(0),
active(1)
}
MAX-ACCESS  read-only
STATUS      current
DESCRIPTION
"Ringer Minor Fail
Values:
inactive(0),
active(1)
"
 ::= { ne843RchEntry  8 }

ne843RchEntryRpff OBJECT-TYPE
SYNTAX      INTEGER {
inactive(0),
active(1)
}
MAX-ACCESS  read-only
STATUS      current
DESCRIPTION
"Ringer Fan Fail
Values:
inactive(0),
active(1)
"
 ::= { ne843RchEntry  9 }

ne843RchEntryRpxj OBJECT-TYPE
SYNTAX      INTEGER {
inactive(0),
active(1)
}
MAX-ACCESS  read-only
STATUS      current
DESCRIPTION
"Ringer Major External Fault
Values:
inactive(0),
active(1)
"
 ::= { ne843RchEntry  10 }

ne843RchEntryRpxn OBJECT-TYPE
SYNTAX      INTEGER {
inactive(0),
active(1)
}
MAX-ACCESS  read-only
STATUS      current
DESCRIPTION
"Ringer Minor External Fault
Values:
inactive(0),
active(1)
"
 ::= { ne843RchEntry  11 }

ne843RchEntryRprl OBJECT-TYPE
SYNTAX      INTEGER {
inactive(0),
active(1)
}
MAX-ACCESS  read-only
STATUS      current
DESCRIPTION
"Ringer Redundancy Loss
Values:
inactive(0),
active(1)
"
 ::= { ne843RchEntry  12 }

ne843RchEntryRpfj OBJECT-TYPE
SYNTAX      INTEGER {
inactive(0),
active(1)
}
MAX-ACCESS  read-only
STATUS      current
DESCRIPTION
"Ringer Major Fail
Values:
inactive(0),
active(1)
"
 ::= { ne843RchEntry  13 }

ne843RchEntryRcdp OBJECT-TYPE
SYNTAX      INTEGER {
inactive(0),
active(1)
}
MAX-ACCESS  read-only
STATUS      current
DESCRIPTION
"Ringer ID Conflict
Values:
inactive(0),
active(1)
"
 ::= { ne843RchEntry  14 }

ne843RchEntryPsn OBJECT-TYPE
SYNTAX      DisplayString
MAX-ACCESS  read-only
STATUS      current
DESCRIPTION
"Primary Serial Number"
 ::= { ne843RchEntry  15 }

ne843RchEntryPtyp OBJECT-TYPE
SYNTAX      DisplayString
MAX-ACCESS  read-only
STATUS      current
DESCRIPTION
"Primary Type"
 ::= { ne843RchEntry  16 }

ne843RchEntryPstt OBJECT-TYPE
SYNTAX      DisplayString
MAX-ACCESS  read-only
STATUS      current
DESCRIPTION
"Primary Ringer State"
 ::= { ne843RchEntry  17 }

ne843RchEntrySsn OBJECT-TYPE
SYNTAX      DisplayString
MAX-ACCESS  read-only
STATUS      current
DESCRIPTION
"Secondary Serial Number"
 ::= { ne843RchEntry  18 }

ne843RchEntryStyp OBJECT-TYPE
SYNTAX      DisplayString
MAX-ACCESS  read-only
STATUS      current
DESCRIPTION
"Secondary Type"
 ::= { ne843RchEntry  19 }

ne843RchEntrySstt OBJECT-TYPE
SYNTAX      DisplayString
MAX-ACCESS  read-only
STATUS      current
DESCRIPTION
"Secondary Ringer State"
 ::= { ne843RchEntry  20 }

ne843RchEntryCap OBJECT-TYPE
SYNTAX      Integer32
UNITS       "VA"
MAX-ACCESS  read-only
STATUS      current
DESCRIPTION
"Capacity (VA)"
 ::= { ne843RchEntry  21 }



--
-- table ALARM
--

ne843AlarmTable    OBJECT-TYPE
SYNTAX SEQUENCE OF Ne843AlarmEntry
MAX-ACCESS not-accessible
STATUS current
DESCRIPTION
        "Table of all Alarm data"
 ::= { ne843  34 }

ne843AlarmEntry OBJECT-TYPE
SYNTAX     Ne843AlarmEntry
MAX-ACCESS  not-accessible
STATUS      current
DESCRIPTION
       "Entry of information for one Alarm"
INDEX { ne843AlarmEntryIndex }
 ::= { ne843AlarmTable  1 }

Ne843AlarmEntry ::= SEQUENCE {
ne843AlarmEntryIndex   INTEGER,
ne843AlarmEntryDes   DisplayString,
ne843AlarmEntryAst   INTEGER,
ne843AlarmEntrySev   DisplayString,
ne843AlarmEntryAcc   DisplayString,
ne843AlarmEntryThr   DisplayString,
ne843AlarmEntryFth   Integer32,
ne843AlarmEntryBth   Integer32,
ne843AlarmEntryDly   Integer32,
ne843AlarmEntryNoo   INTEGER,
ne843AlarmEntryNor   INTEGER,
ne843AlarmEntryNag   INTEGER,
ne843AlarmEntryDst   DisplayString
}

ne843AlarmEntryIndex OBJECT-TYPE
SYNTAX      INTEGER (0..2147483647)
MAX-ACCESS  read-only
STATUS      current
DESCRIPTION
"Table Index"
 ::= { ne843AlarmEntry  1 }

ne843AlarmEntryDes OBJECT-TYPE
SYNTAX      DisplayString
MAX-ACCESS  read-write
STATUS      current
DESCRIPTION
"Description"
 ::= { ne843AlarmEntry  2 }

ne843AlarmEntryAst OBJECT-TYPE
SYNTAX      INTEGER {
inactive(0),
active(1)
}
MAX-ACCESS  read-only
STATUS      current
DESCRIPTION
"State
Values:
inactive(0),
active(1)
"
 ::= { ne843AlarmEntry  3 }

ne843AlarmEntrySev OBJECT-TYPE
SYNTAX      DisplayString
MAX-ACCESS  read-write
STATUS      current
DESCRIPTION
"Severity"
 ::= { ne843AlarmEntry  4 }

ne843AlarmEntryAcc OBJECT-TYPE
SYNTAX      DisplayString
MAX-ACCESS  read-write
STATUS      current
DESCRIPTION
"Contact Closure
Values:
,
R1,
R2,
R3,
R4,
R5,
R6,
R7
"
 ::= { ne843AlarmEntry  5 }

ne843AlarmEntryThr OBJECT-TYPE
SYNTAX      DisplayString
MAX-ACCESS  read-write
STATUS      current
DESCRIPTION
"Threshold"
 ::= { ne843AlarmEntry  6 }

ne843AlarmEntryFth OBJECT-TYPE
SYNTAX      Integer32
UNITS       "mV"
MAX-ACCESS  read-write
STATUS      current
DESCRIPTION
"Float Threshold (mV)"
 ::= { ne843AlarmEntry  7 }

ne843AlarmEntryBth OBJECT-TYPE
SYNTAX      Integer32
UNITS       "mV"
MAX-ACCESS  read-write
STATUS      current
DESCRIPTION
"Boost Threshold (mV)"
 ::= { ne843AlarmEntry  8 }

ne843AlarmEntryDly OBJECT-TYPE
SYNTAX      Integer32(0..540)
UNITS       "Seconds"
MAX-ACCESS  read-write
STATUS      current
DESCRIPTION
"Notify Delay (Seconds)"
 ::= { ne843AlarmEntry  9 }

ne843AlarmEntryNoo OBJECT-TYPE
SYNTAX      INTEGER {
no(0),
yes(1)
}
MAX-ACCESS  read-write
STATUS      current
DESCRIPTION
"Notify On Occur
Values:
no(0),
yes(1)
"
 ::= { ne843AlarmEntry  10 }

ne843AlarmEntryNor OBJECT-TYPE
SYNTAX      INTEGER {
no(0),
yes(1)
}
MAX-ACCESS  read-write
STATUS      current
DESCRIPTION
"Notify On Retire
Values:
no(0),
yes(1)
"
 ::= { ne843AlarmEntry  11 }

ne843AlarmEntryNag OBJECT-TYPE
SYNTAX      INTEGER {
no(0),
yes(1)
}
MAX-ACCESS  read-write
STATUS      current
DESCRIPTION
"Nag on Occur
Values:
no(0),
yes(1)
"
 ::= { ne843AlarmEntry  12 }

ne843AlarmEntryDst OBJECT-TYPE
SYNTAX      DisplayString
MAX-ACCESS  read-write
STATUS      current
DESCRIPTION
"Notify Destination"
 ::= { ne843AlarmEntry  13 }



--
-- object ne843Trap
--

ne843Trap OBJECT IDENTIFIER  ::= { ne843  35 }


--
-- object ne843TrapInfo
--

ne843TrapInfo OBJECT IDENTIFIER  ::= { ne843  36 }

ne843TrapDesc OBJECT-TYPE
SYNTAX      DisplayString
MAX-ACCESS  accessible-for-notify
STATUS      current
DESCRIPTION
        "Event Description"
 ::= { ne843TrapInfo  1 }

ne843TrapSev OBJECT-TYPE
SYNTAX      INTEGER {
	        retire(0),
	        record(1),
	        warning(2),
	        minor(3),
	        major(4),
	        critical(5)
	      }
MAX-ACCESS  accessible-for-notify
STATUS      current
DESCRIPTION
        "Event Severity"
 ::= { ne843TrapInfo  2 }

ne843TrapTime OBJECT-TYPE
SYNTAX      DisplayString
MAX-ACCESS  accessible-for-notify
STATUS      current
DESCRIPTION
        "Time of Event"
 ::= { ne843TrapInfo  3 }

ne843TrapDate OBJECT-TYPE
SYNTAX      DisplayString
MAX-ACCESS  accessible-for-notify
STATUS      current
DESCRIPTION
        "Date of Event"
 ::= { ne843TrapInfo  4 }

ne843TrapPath OBJECT-TYPE
SYNTAX      DisplayString
MAX-ACCESS  accessible-for-notify
STATUS      current
DESCRIPTION
        "T1.317 Path of Event"
 ::= { ne843TrapInfo  5 }


ne843TrapDc1Amj   NOTIFICATION-TYPE
OBJECTS     { ne843TrapDesc, ne843TrapSev, ne843TrapTime, ne843TrapDate, ne843TrapPath }
STATUS      current
DESCRIPTION
        "Auxiliary Fuse Major"
 ::= { ne843Trap  1 }

ne843TrapDc1Vsf   NOTIFICATION-TYPE
OBJECTS     { ne843TrapDesc, ne843TrapSev, ne843TrapTime, ne843TrapDate, ne843TrapPath }
STATUS      current
DESCRIPTION
        "Sense/Control Fuse"
 ::= { ne843Trap  2 }

ne843TrapDc1Osa   NOTIFICATION-TYPE
OBJECTS     { ne843TrapDesc, ne843TrapSev, ne843TrapTime, ne843TrapDate, ne843TrapPath }
STATUS      current
DESCRIPTION
        "Open String"
 ::= { ne843Trap  3 }

ne843TrapDc1Zid   NOTIFICATION-TYPE
OBJECTS     { ne843TrapDesc, ne843TrapSev, ne843TrapTime, ne843TrapDate, ne843TrapPath }
STATUS      current
DESCRIPTION
        "ID Not Configured"
 ::= { ne843Trap  4 }

ne843TrapDc1Tpa   NOTIFICATION-TYPE
OBJECTS     { ne843TrapDesc, ne843TrapSev, ne843TrapTime, ne843TrapDate, ne843TrapPath }
STATUS      current
DESCRIPTION
        "Thermal Probe Alarm"
 ::= { ne843Trap  5 }

ne843TrapDc1Vmf   NOTIFICATION-TYPE
OBJECTS     { ne843TrapDesc, ne843TrapSev, ne843TrapTime, ne843TrapDate, ne843TrapPath }
STATUS      current
DESCRIPTION
        "Voltage Module Fail"
 ::= { ne843Trap  6 }

ne843TrapDc1Cma   NOTIFICATION-TYPE
OBJECTS     { ne843TrapDesc, ne843TrapSev, ne843TrapTime, ne843TrapDate, ne843TrapPath }
STATUS      current
DESCRIPTION
        "Minor Communication Failure"
 ::= { ne843Trap  7 }

ne843TrapDc1Mcm   NOTIFICATION-TYPE
OBJECTS     { ne843TrapDesc, ne843TrapSev, ne843TrapTime, ne843TrapDate, ne843TrapPath }
STATUS      current
DESCRIPTION
        "Major Communication Failure"
 ::= { ne843Trap  8 }

ne843TrapDc1Epo   NOTIFICATION-TYPE
OBJECTS     { ne843TrapDesc, ne843TrapSev, ne843TrapTime, ne843TrapDate, ne843TrapPath }
STATUS      current
DESCRIPTION
        "Emergency Power Off"
 ::= { ne843Trap  9 }

ne843TrapDc1Icr   NOTIFICATION-TYPE
OBJECTS     { ne843TrapDesc, ne843TrapSev, ne843TrapTime, ne843TrapDate, ne843TrapPath }
STATUS      current
DESCRIPTION
        "Incompatible Rectifier"
 ::= { ne843Trap  10 }

ne843TrapDc1Rfa   NOTIFICATION-TYPE
OBJECTS     { ne843TrapDesc, ne843TrapSev, ne843TrapTime, ne843TrapDate, ne843TrapPath }
STATUS      current
DESCRIPTION
        "Rectifier Fail"
 ::= { ne843Trap  11 }

ne843TrapDc1Acf   NOTIFICATION-TYPE
OBJECTS     { ne843TrapDesc, ne843TrapSev, ne843TrapTime, ne843TrapDate, ne843TrapPath }
STATUS      current
DESCRIPTION
        "AC Fail"
 ::= { ne843Trap  12 }

ne843TrapDc1Man   NOTIFICATION-TYPE
OBJECTS     { ne843TrapDesc, ne843TrapSev, ne843TrapTime, ne843TrapDate, ne843TrapPath }
STATUS      current
DESCRIPTION
        "Manual Off"
 ::= { ne843Trap  13 }

ne843TrapDc1Did   NOTIFICATION-TYPE
OBJECTS     { ne843TrapDesc, ne843TrapSev, ne843TrapTime, ne843TrapDate, ne843TrapPath }
STATUS      current
DESCRIPTION
        "ID Conflict"
 ::= { ne843Trap  14 }

ne843TrapDc1Clm   NOTIFICATION-TYPE
OBJECTS     { ne843TrapDesc, ne843TrapSev, ne843TrapTime, ne843TrapDate, ne843TrapPath }
STATUS      current
DESCRIPTION
        "Rectifier Current Limit"
 ::= { ne843Trap  15 }

ne843TrapDc1Rfn   NOTIFICATION-TYPE
OBJECTS     { ne843TrapDesc, ne843TrapSev, ne843TrapTime, ne843TrapDate, ne843TrapPath }
STATUS      current
DESCRIPTION
        "Rectifier Fan Failure"
 ::= { ne843Trap  16 }

ne843TrapDc1Vla   NOTIFICATION-TYPE
OBJECTS     { ne843TrapDesc, ne843TrapSev, ne843TrapTime, ne843TrapDate, ne843TrapPath }
STATUS      current
DESCRIPTION
        "Very Low Voltage"
 ::= { ne843Trap  17 }

ne843TrapDc1Mfa   NOTIFICATION-TYPE
OBJECTS     { ne843TrapDesc, ne843TrapSev, ne843TrapTime, ne843TrapDate, ne843TrapPath }
STATUS      current
DESCRIPTION
        "Multiple Rectifier Fail"
 ::= { ne843Trap  18 }

ne843TrapDc1Rtl   NOTIFICATION-TYPE
OBJECTS     { ne843TrapDesc, ne843TrapSev, ne843TrapTime, ne843TrapDate, ne843TrapPath }
STATUS      current
DESCRIPTION
        "Reserve Time Low"
 ::= { ne843Trap  19 }

ne843TrapDc1Rrtl   NOTIFICATION-TYPE
OBJECTS     { ne843TrapDesc, ne843TrapSev, ne843TrapTime, ne843TrapDate, ne843TrapPath }
STATUS      current
DESCRIPTION
        "Real-time Reserve Time Low"
 ::= { ne843Trap  20 }

ne843TrapDc1Rls   NOTIFICATION-TYPE
OBJECTS     { ne843TrapDesc, ne843TrapSev, ne843TrapTime, ne843TrapDate, ne843TrapPath }
STATUS      current
DESCRIPTION
        "Redundancy Loss"
 ::= { ne843Trap  21 }

ne843TrapDc1Mman   NOTIFICATION-TYPE
OBJECTS     { ne843TrapDesc, ne843TrapSev, ne843TrapTime, ne843TrapDate, ne843TrapPath }
STATUS      current
DESCRIPTION
        "Multiple Manual Off"
 ::= { ne843Trap  22 }

ne843TrapDc1Macf   NOTIFICATION-TYPE
OBJECTS     { ne843TrapDesc, ne843TrapSev, ne843TrapTime, ne843TrapDate, ne843TrapPath }
STATUS      current
DESCRIPTION
        "Multiple AC Failure"
 ::= { ne843Trap  23 }

ne843TrapDc1Bda   NOTIFICATION-TYPE
OBJECTS     { ne843TrapDesc, ne843TrapSev, ne843TrapTime, ne843TrapDate, ne843TrapPath }
STATUS      current
DESCRIPTION
        "Battery On Discharge"
 ::= { ne843Trap  24 }

ne843TrapDc1Hva   NOTIFICATION-TYPE
OBJECTS     { ne843TrapDesc, ne843TrapSev, ne843TrapTime, ne843TrapDate, ne843TrapPath }
STATUS      current
DESCRIPTION
        "High Voltage"
 ::= { ne843Trap  25 }

ne843TrapDc1Hfv   NOTIFICATION-TYPE
OBJECTS     { ne843TrapDesc, ne843TrapSev, ne843TrapTime, ne843TrapDate, ne843TrapPath }
STATUS      current
DESCRIPTION
        "High Float Voltage"
 ::= { ne843Trap  26 }

ne843TrapPs1Epr   NOTIFICATION-TYPE
OBJECTS     { ne843TrapDesc, ne843TrapSev, ne843TrapTime, ne843TrapDate, ne843TrapPath }
STATUS      current
DESCRIPTION
        "External Password Reset"
 ::= { ne843Trap  27 }

ne843TrapPs1Pfd   NOTIFICATION-TYPE
OBJECTS     { ne843TrapDesc, ne843TrapSev, ne843TrapTime, ne843TrapDate, ne843TrapPath }
STATUS      current
DESCRIPTION
        "Passwords At Default"
 ::= { ne843Trap  28 }

ne843TrapPs1Exl   NOTIFICATION-TYPE
OBJECTS     { ne843TrapDesc, ne843TrapSev, ne843TrapTime, ne843TrapDate, ne843TrapPath }
STATUS      current
DESCRIPTION
        "Excessive Login Attempts"
 ::= { ne843Trap  29 }

ne843TrapPs1Bbl   NOTIFICATION-TYPE
OBJECTS     { ne843TrapDesc, ne843TrapSev, ne843TrapTime, ne843TrapDate, ne843TrapPath }
STATUS      current
DESCRIPTION
        "Memory Backup Battery Low"
 ::= { ne843Trap  30 }

ne843TrapPs1Clc   NOTIFICATION-TYPE
OBJECTS     { ne843TrapDesc, ne843TrapSev, ne843TrapTime, ne843TrapDate, ne843TrapPath }
STATUS      current
DESCRIPTION
        "Clock Changed"
 ::= { ne843Trap  31 }

ne843TrapPs1Stf   NOTIFICATION-TYPE
OBJECTS     { ne843TrapDesc, ne843TrapSev, ne843TrapTime, ne843TrapDate, ne843TrapPath }
STATUS      current
DESCRIPTION
        "Self Test Failed"
 ::= { ne843Trap  32 }

ne843TrapPs1Pgi   NOTIFICATION-TYPE
OBJECTS     { ne843TrapDesc, ne843TrapSev, ne843TrapTime, ne843TrapDate, ne843TrapPath }
STATUS      current
DESCRIPTION
        "Program Line Invalid"
 ::= { ne843Trap  33 }

ne843TrapPs1Cch   NOTIFICATION-TYPE
OBJECTS     { ne843TrapDesc, ne843TrapSev, ne843TrapTime, ne843TrapDate, ne843TrapPath }
STATUS      current
DESCRIPTION
        "Configuration Changed"
 ::= { ne843Trap  34 }

ne843TrapPs1Hcl   NOTIFICATION-TYPE
OBJECTS     { ne843TrapDesc, ne843TrapSev, ne843TrapTime, ne843TrapDate, ne843TrapPath }
STATUS      current
DESCRIPTION
        "History Cleared"
 ::= { ne843Trap  35 }

ne843TrapPs1Ax1   NOTIFICATION-TYPE
OBJECTS     { ne843TrapDesc, ne843TrapSev, ne843TrapTime, ne843TrapDate, ne843TrapPath }
STATUS      current
DESCRIPTION
        "Auxiliary Event 1"
 ::= { ne843Trap  36 }

ne843TrapPs1Ax2   NOTIFICATION-TYPE
OBJECTS     { ne843TrapDesc, ne843TrapSev, ne843TrapTime, ne843TrapDate, ne843TrapPath }
STATUS      current
DESCRIPTION
        "Auxiliary Event 2"
 ::= { ne843Trap  37 }

ne843TrapPs1Ax3   NOTIFICATION-TYPE
OBJECTS     { ne843TrapDesc, ne843TrapSev, ne843TrapTime, ne843TrapDate, ne843TrapPath }
STATUS      current
DESCRIPTION
        "Auxiliary Event 3"
 ::= { ne843Trap  38 }

ne843TrapPs1Ax4   NOTIFICATION-TYPE
OBJECTS     { ne843TrapDesc, ne843TrapSev, ne843TrapTime, ne843TrapDate, ne843TrapPath }
STATUS      current
DESCRIPTION
        "Auxiliary Event 4"
 ::= { ne843Trap  39 }

ne843TrapPs1Ax5   NOTIFICATION-TYPE
OBJECTS     { ne843TrapDesc, ne843TrapSev, ne843TrapTime, ne843TrapDate, ne843TrapPath }
STATUS      current
DESCRIPTION
        "Auxiliary Event 5"
 ::= { ne843Trap  40 }

ne843TrapPs1Ax6   NOTIFICATION-TYPE
OBJECTS     { ne843TrapDesc, ne843TrapSev, ne843TrapTime, ne843TrapDate, ne843TrapPath }
STATUS      current
DESCRIPTION
        "Auxiliary Event 6"
 ::= { ne843Trap  41 }

ne843TrapPs1Fan24   NOTIFICATION-TYPE
OBJECTS     { ne843TrapDesc, ne843TrapSev, ne843TrapTime, ne843TrapDate, ne843TrapPath }
STATUS      current
DESCRIPTION
        "24 V Fuse Minor"
 ::= { ne843Trap  42 }

ne843TrapPs1Fan48   NOTIFICATION-TYPE
OBJECTS     { ne843TrapDesc, ne843TrapSev, ne843TrapTime, ne843TrapDate, ne843TrapPath }
STATUS      current
DESCRIPTION
        "48 V Fuse Minor"
 ::= { ne843Trap  43 }

ne843TrapPs1Faj24   NOTIFICATION-TYPE
OBJECTS     { ne843TrapDesc, ne843TrapSev, ne843TrapTime, ne843TrapDate, ne843TrapPath }
STATUS      current
DESCRIPTION
        "24 V Fuse Major"
 ::= { ne843Trap  44 }

ne843TrapPs1Faj48   NOTIFICATION-TYPE
OBJECTS     { ne843TrapDesc, ne843TrapSev, ne843TrapTime, ne843TrapDate, ne843TrapPath }
STATUS      current
DESCRIPTION
        "48 V Fuse Major"
 ::= { ne843Trap  45 }

ne843TrapAt1Ata   NOTIFICATION-TYPE
OBJECTS     { ne843TrapDesc, ne843TrapSev, ne843TrapTime, ne843TrapDate, ne843TrapPath }
STATUS      current
DESCRIPTION
        "Alarm Test Active"
 ::= { ne843Trap  46 }

ne843TrapAt1Atb   NOTIFICATION-TYPE
OBJECTS     { ne843TrapDesc, ne843TrapSev, ne843TrapTime, ne843TrapDate, ne843TrapPath }
STATUS      current
DESCRIPTION
        "Alarm Test Aborted"
 ::= { ne843Trap  47 }

ne843TrapCp1Cfa   NOTIFICATION-TYPE
OBJECTS     { ne843TrapDesc, ne843TrapSev, ne843TrapTime, ne843TrapDate, ne843TrapPath }
STATUS      current
DESCRIPTION
        "Converter Fail"
 ::= { ne843Trap  48 }

ne843TrapCp1Cfn   NOTIFICATION-TYPE
OBJECTS     { ne843TrapDesc, ne843TrapSev, ne843TrapTime, ne843TrapDate, ne843TrapPath }
STATUS      current
DESCRIPTION
        "Converter Fan Minor"
 ::= { ne843Trap  49 }

ne843TrapCp1Cfj   NOTIFICATION-TYPE
OBJECTS     { ne843TrapDesc, ne843TrapSev, ne843TrapTime, ne843TrapDate, ne843TrapPath }
STATUS      current
DESCRIPTION
        "Converter Fan Major"
 ::= { ne843Trap  50 }

ne843TrapCp1Dfa   NOTIFICATION-TYPE
OBJECTS     { ne843TrapDesc, ne843TrapSev, ne843TrapTime, ne843TrapDate, ne843TrapPath }
STATUS      current
DESCRIPTION
        "Distribution Fail"
 ::= { ne843Trap  51 }

ne843TrapCp1Did   NOTIFICATION-TYPE
OBJECTS     { ne843TrapDesc, ne843TrapSev, ne843TrapTime, ne843TrapDate, ne843TrapPath }
STATUS      current
DESCRIPTION
        "ID Conflict"
 ::= { ne843Trap  52 }

ne843TrapCp1Icc   NOTIFICATION-TYPE
OBJECTS     { ne843TrapDesc, ne843TrapSev, ne843TrapTime, ne843TrapDate, ne843TrapPath }
STATUS      current
DESCRIPTION
        "Incompatible Converter Alarm"
 ::= { ne843Trap  53 }

ne843TrapCp1Mfa   NOTIFICATION-TYPE
OBJECTS     { ne843TrapDesc, ne843TrapSev, ne843TrapTime, ne843TrapDate, ne843TrapPath }
STATUS      current
DESCRIPTION
        "Multiple Converter Fail"
 ::= { ne843Trap  54 }

ne843TrapCp1Hva   NOTIFICATION-TYPE
OBJECTS     { ne843TrapDesc, ne843TrapSev, ne843TrapTime, ne843TrapDate, ne843TrapPath }
STATUS      current
DESCRIPTION
        "Converter High Voltage Major"
 ::= { ne843Trap  55 }

ne843TrapCp1Hfv   NOTIFICATION-TYPE
OBJECTS     { ne843TrapDesc, ne843TrapSev, ne843TrapTime, ne843TrapDate, ne843TrapPath }
STATUS      current
DESCRIPTION
        "Converter High Voltage Minor"
 ::= { ne843Trap  56 }

ne843TrapCp1Vla   NOTIFICATION-TYPE
OBJECTS     { ne843TrapDesc, ne843TrapSev, ne843TrapTime, ne843TrapDate, ne843TrapPath }
STATUS      current
DESCRIPTION
        "Converter Very Low Voltage"
 ::= { ne843Trap  57 }

ne843TrapCp1Rl   NOTIFICATION-TYPE
OBJECTS     { ne843TrapDesc, ne843TrapSev, ne843TrapTime, ne843TrapDate, ne843TrapPath }
STATUS      current
DESCRIPTION
        "Converter Redundancy Loss"
 ::= { ne843Trap  58 }

ne843TrapBr1Bta   NOTIFICATION-TYPE
OBJECTS     { ne843TrapDesc, ne843TrapSev, ne843TrapTime, ne843TrapDate, ne843TrapPath }
STATUS      current
DESCRIPTION
        "Battery Test Active"
 ::= { ne843Trap  59 }

ne843TrapBr1Bfa   NOTIFICATION-TYPE
OBJECTS     { ne843TrapDesc, ne843TrapSev, ne843TrapTime, ne843TrapDate, ne843TrapPath }
STATUS      current
DESCRIPTION
        "Battery Test Failed"
 ::= { ne843Trap  60 }

ne843TrapBr1Scda   NOTIFICATION-TYPE
OBJECTS     { ne843TrapDesc, ne843TrapSev, ne843TrapTime, ne843TrapDate, ne843TrapPath }
STATUS      current
DESCRIPTION
        "Shorted Cell Detected"
 ::= { ne843Trap  61 }

ne843TrapBr1Isda   NOTIFICATION-TYPE
OBJECTS     { ne843TrapDesc, ne843TrapSev, ne843TrapTime, ne843TrapDate, ne843TrapPath }
STATUS      current
DESCRIPTION
        "Imminent Shutdown"
 ::= { ne843Trap  62 }

ne843TrapBr1Mdp   NOTIFICATION-TYPE
OBJECTS     { ne843TrapDesc, ne843TrapSev, ne843TrapTime, ne843TrapDate, ne843TrapPath }
STATUS      current
DESCRIPTION
        "Voltage Duplicate ID"
 ::= { ne843Trap  63 }

ne843TrapBr1Mzd   NOTIFICATION-TYPE
OBJECTS     { ne843TrapDesc, ne843TrapSev, ne843TrapTime, ne843TrapDate, ne843TrapPath }
STATUS      current
DESCRIPTION
        "Voltage ID Not Configured"
 ::= { ne843Trap  64 }

ne843TrapBr1Btha   NOTIFICATION-TYPE
OBJECTS     { ne843TrapDesc, ne843TrapSev, ne843TrapTime, ne843TrapDate, ne843TrapPath }
STATUS      current
DESCRIPTION
        "High Battery Temperature"
 ::= { ne843Trap  65 }

ne843TrapCn1Cno   NOTIFICATION-TYPE
OBJECTS     { ne843TrapDesc, ne843TrapSev, ne843TrapTime, ne843TrapDate, ne843TrapPath }
STATUS      current
DESCRIPTION
        "Contactor Open"
 ::= { ne843Trap  66 }

ne843TrapCn1Cnf   NOTIFICATION-TYPE
OBJECTS     { ne843TrapDesc, ne843TrapSev, ne843TrapTime, ne843TrapDate, ne843TrapPath }
STATUS      current
DESCRIPTION
        "Contactor Failed"
 ::= { ne843Trap  67 }

ne843TrapCn2Cno   NOTIFICATION-TYPE
OBJECTS     { ne843TrapDesc, ne843TrapSev, ne843TrapTime, ne843TrapDate, ne843TrapPath }
STATUS      current
DESCRIPTION
        "Contactor Open"
 ::= { ne843Trap  68 }

ne843TrapCn2Cnf   NOTIFICATION-TYPE
OBJECTS     { ne843TrapDesc, ne843TrapSev, ne843TrapTime, ne843TrapDate, ne843TrapPath }
STATUS      current
DESCRIPTION
        "Contactor Failed"
 ::= { ne843Trap  69 }

ne843TrapCn3Cno   NOTIFICATION-TYPE
OBJECTS     { ne843TrapDesc, ne843TrapSev, ne843TrapTime, ne843TrapDate, ne843TrapPath }
STATUS      current
DESCRIPTION
        "Contactor Open"
 ::= { ne843Trap  70 }

ne843TrapCn3Cnf   NOTIFICATION-TYPE
OBJECTS     { ne843TrapDesc, ne843TrapSev, ne843TrapTime, ne843TrapDate, ne843TrapPath }
STATUS      current
DESCRIPTION
        "Contactor Failed"
 ::= { ne843Trap  71 }

ne843TrapCn4Cno   NOTIFICATION-TYPE
OBJECTS     { ne843TrapDesc, ne843TrapSev, ne843TrapTime, ne843TrapDate, ne843TrapPath }
STATUS      current
DESCRIPTION
        "Contactor Open"
 ::= { ne843Trap  72 }

ne843TrapCn4Cnf   NOTIFICATION-TYPE
OBJECTS     { ne843TrapDesc, ne843TrapSev, ne843TrapTime, ne843TrapDate, ne843TrapPath }
STATUS      current
DESCRIPTION
        "Contactor Failed"
 ::= { ne843Trap  73 }

ne843TrapCm1Cof   NOTIFICATION-TYPE
OBJECTS     { ne843TrapDesc, ne843TrapSev, ne843TrapTime, ne843TrapDate, ne843TrapPath }
STATUS      current
DESCRIPTION
        "Queue Overflow"
 ::= { ne843Trap  74 }

ne843TrapCm1Cor   NOTIFICATION-TYPE
OBJECTS     { ne843TrapDesc, ne843TrapSev, ne843TrapTime, ne843TrapDate, ne843TrapPath }
STATUS      current
DESCRIPTION
        "Number Did Not Respond"
 ::= { ne843Trap  75 }

ne843TrapCm1Nnc   NOTIFICATION-TYPE
OBJECTS     { ne843TrapDesc, ne843TrapSev, ne843TrapTime, ne843TrapDate, ne843TrapPath }
STATUS      current
DESCRIPTION
        "Number Not Configured"
 ::= { ne843Trap  76 }

ne843TrapPo1Por   NOTIFICATION-TYPE
OBJECTS     { ne843TrapDesc, ne843TrapSev, ne843TrapTime, ne843TrapDate, ne843TrapPath }
STATUS      current
DESCRIPTION
        "Number Did Not Respond"
 ::= { ne843Trap  77 }

ne843TrapRp1Rf   NOTIFICATION-TYPE
OBJECTS     { ne843TrapDesc, ne843TrapSev, ne843TrapTime, ne843TrapDate, ne843TrapPath }
STATUS      current
DESCRIPTION
        "Ringer Minor Fail"
 ::= { ne843Trap  78 }

ne843TrapRp1Rpff   NOTIFICATION-TYPE
OBJECTS     { ne843TrapDesc, ne843TrapSev, ne843TrapTime, ne843TrapDate, ne843TrapPath }
STATUS      current
DESCRIPTION
        "Ringer Fan Fail"
 ::= { ne843Trap  79 }

ne843TrapRp1Rprl   NOTIFICATION-TYPE
OBJECTS     { ne843TrapDesc, ne843TrapSev, ne843TrapTime, ne843TrapDate, ne843TrapPath }
STATUS      current
DESCRIPTION
        "Ringer Redundancy Loss"
 ::= { ne843Trap  80 }

ne843TrapRp1Rpfj   NOTIFICATION-TYPE
OBJECTS     { ne843TrapDesc, ne843TrapSev, ne843TrapTime, ne843TrapDate, ne843TrapPath }
STATUS      current
DESCRIPTION
        "Ringer Major Fail"
 ::= { ne843Trap  81 }

ne843TrapRp1Rpxj   NOTIFICATION-TYPE
OBJECTS     { ne843TrapDesc, ne843TrapSev, ne843TrapTime, ne843TrapDate, ne843TrapPath }
STATUS      current
DESCRIPTION
        "Ringer Major External Fault"
 ::= { ne843Trap  82 }

ne843TrapRp1Rpxn   NOTIFICATION-TYPE
OBJECTS     { ne843TrapDesc, ne843TrapSev, ne843TrapTime, ne843TrapDate, ne843TrapPath }
STATUS      current
DESCRIPTION
        "Ringer Minor External Fault"
 ::= { ne843Trap  83 }

ne843TrapRp1Rcdp   NOTIFICATION-TYPE
OBJECTS     { ne843TrapDesc, ne843TrapSev, ne843TrapTime, ne843TrapDate, ne843TrapPath }
STATUS      current
DESCRIPTION
        "Ringer ID Conflict"
 ::= { ne843Trap  84 }

ne843TrapUserDefined   NOTIFICATION-TYPE
OBJECTS     { ne843TrapDesc, ne843TrapSev, ne843TrapTime, ne843TrapDate, ne843TrapPath }
STATUS      current
DESCRIPTION
        "This may be a user defined event, or a new controller event."
 ::= { ne843Trap  85 }

ne843TrapDc1Emd   NOTIFICATION-TYPE
OBJECTS     { ne843TrapDesc, ne843TrapSev, ne843TrapTime, ne843TrapDate, ne843TrapPath }
STATUS      current
DESCRIPTION
        "Energy Management Disabled"
 ::= { ne843Trap  86 }

ne843TrapDc1Pfs   NOTIFICATION-TYPE
OBJECTS     { ne843TrapDesc, ne843TrapSev, ne843TrapTime, ne843TrapDate, ne843TrapPath }
STATUS      current
DESCRIPTION
        "Thermal Probe Fail Safe"
 ::= { ne843Trap  87 }

ne843TrapDc1Rif   NOTIFICATION-TYPE
OBJECTS     { ne843TrapDesc, ne843TrapSev, ne843TrapTime, ne843TrapDate, ne843TrapPath }
STATUS      current
DESCRIPTION
        "Rectifier Internal Fault"
 ::= { ne843Trap  88 }

ne843TrapDc1Lsf   NOTIFICATION-TYPE
OBJECTS     { ne843TrapDesc, ne843TrapSev, ne843TrapTime, ne843TrapDate, ne843TrapPath }
STATUS      current
DESCRIPTION
        "Load Share Fail"
 ::= { ne843Trap  89 }

ne843TrapPs1Ax7   NOTIFICATION-TYPE
OBJECTS     { ne843TrapDesc, ne843TrapSev, ne843TrapTime, ne843TrapDate, ne843TrapPath }
STATUS      current
DESCRIPTION
        "Auxiliary Event 7"
 ::= { ne843Trap  90 }

ne843TrapPs1Ax8   NOTIFICATION-TYPE
OBJECTS     { ne843TrapDesc, ne843TrapSev, ne843TrapTime, ne843TrapDate, ne843TrapPath }
STATUS      current
DESCRIPTION
        "Auxiliary Event 8"
 ::= { ne843Trap  91 }

ne843TrapPs1Ax9   NOTIFICATION-TYPE
OBJECTS     { ne843TrapDesc, ne843TrapSev, ne843TrapTime, ne843TrapDate, ne843TrapPath }
STATUS      current
DESCRIPTION
        "Auxiliary Event 9"
 ::= { ne843Trap  92 }

ne843TrapPs1Ax10   NOTIFICATION-TYPE
OBJECTS     { ne843TrapDesc, ne843TrapSev, ne843TrapTime, ne843TrapDate, ne843TrapPath }
STATUS      current
DESCRIPTION
        "Auxiliary Event 10"
 ::= { ne843Trap  93 }

ne843TrapPs1Ax11   NOTIFICATION-TYPE
OBJECTS     { ne843TrapDesc, ne843TrapSev, ne843TrapTime, ne843TrapDate, ne843TrapPath }
STATUS      current
DESCRIPTION
        "Auxiliary Event 11"
 ::= { ne843Trap  94 }

ne843TrapPs1Ax12   NOTIFICATION-TYPE
OBJECTS     { ne843TrapDesc, ne843TrapSev, ne843TrapTime, ne843TrapDate, ne843TrapPath }
STATUS      current
DESCRIPTION
        "Auxiliary Event 12"
 ::= { ne843Trap  95 }

ne843TrapBr1Btla   NOTIFICATION-TYPE
OBJECTS     { ne843TrapDesc, ne843TrapSev, ne843TrapTime, ne843TrapDate, ne843TrapPath }
STATUS      current
DESCRIPTION
        "Low Battery Temperature"
 ::= { ne843Trap  96 }

ne843TrapBr1Btvh   NOTIFICATION-TYPE
OBJECTS     { ne843TrapDesc, ne843TrapSev, ne843TrapTime, ne843TrapDate, ne843TrapPath }
STATUS      current
DESCRIPTION
        "Very High Battery Temperature"
 ::= { ne843Trap  97 }

ne843TrapBr1Btvl   NOTIFICATION-TYPE
OBJECTS     { ne843TrapDesc, ne843TrapSev, ne843TrapTime, ne843TrapDate, ne843TrapPath }
STATUS      current
DESCRIPTION
        "Very Low Battery Temperature"
 ::= { ne843Trap  98 }

ne843TrapGn1Gnr   NOTIFICATION-TYPE
OBJECTS     { ne843TrapDesc, ne843TrapSev, ne843TrapTime, ne843TrapDate, ne843TrapPath }
STATUS      current
DESCRIPTION
        "Generator Running"
 ::= { ne843Trap  99 }

ne843TrapGn1Gnm   NOTIFICATION-TYPE
OBJECTS     { ne843TrapDesc, ne843TrapSev, ne843TrapTime, ne843TrapDate, ne843TrapPath }
STATUS      current
DESCRIPTION
        "Generator Maintenance Required"
 ::= { ne843Trap  100 }

ne843TrapGn1Gnf   NOTIFICATION-TYPE
OBJECTS     { ne843TrapDesc, ne843TrapSev, ne843TrapTime, ne843TrapDate, ne843TrapPath }
STATUS      current
DESCRIPTION
        "Generator Fail"
 ::= { ne843Trap  101 }

ne843TrapPs1Amtl   NOTIFICATION-TYPE
OBJECTS     { ne843TrapDesc, ne843TrapSev, ne843TrapTime, ne843TrapDate, ne843TrapPath }
STATUS      current
DESCRIPTION
        "Low Ambient Temperature"
 ::= { ne843Trap  102 }

ne843TrapPs1Amth   NOTIFICATION-TYPE
OBJECTS     { ne843TrapDesc, ne843TrapSev, ne843TrapTime, ne843TrapDate, ne843TrapPath }
STATUS      current
DESCRIPTION
        "High Ambient Temperature"
 ::= { ne843Trap  103 }

ne843TrapAco1Aac   NOTIFICATION-TYPE
OBJECTS     { ne843TrapDesc, ne843TrapSev, ne843TrapTime, ne843TrapDate, ne843TrapPath }
STATUS      current
DESCRIPTION
        "ACO Active"
 ::= { ne843Trap  104 }

ne843TrapBr1Rba   NOTIFICATION-TYPE
OBJECTS     { ne843TrapDesc, ne843TrapSev, ne843TrapTime, ne843TrapDate, ne843TrapPath }
STATUS      current
DESCRIPTION
        "Reverse Battery"
 ::= { ne843Trap  105 }

ne843TrapCp1Cin   NOTIFICATION-TYPE
OBJECTS     { ne843TrapDesc, ne843TrapSev, ne843TrapTime, ne843TrapDate, ne843TrapPath }
STATUS      current
DESCRIPTION
        "Converter Input Fail"
 ::= { ne843Trap  106 }

ne843TrapDc1Bof   NOTIFICATION-TYPE
OBJECTS     { ne843TrapDesc, ne843TrapSev, ne843TrapTime, ne843TrapDate, ne843TrapPath }
STATUS      current
DESCRIPTION
        "Rectifier ORing FET Fault"
 ::= { ne843Trap  107 }

ne843TrapDc1Sof   NOTIFICATION-TYPE
OBJECTS     { ne843TrapDesc, ne843TrapSev, ne843TrapTime, ne843TrapDate, ne843TrapPath }
STATUS      current
DESCRIPTION
        "Rectifier Shorted ORing FET"
 ::= { ne843Trap  108 }

ne843TrapDc1Der   NOTIFICATION-TYPE
OBJECTS     { ne843TrapDesc, ne843TrapSev, ne843TrapTime, ne843TrapDate, ne843TrapPath }
STATUS      current
DESCRIPTION
        "Rectifier Under Voltage"
 ::= { ne843Trap  109 }

ne843TrapGn1Gns   NOTIFICATION-TYPE
OBJECTS     { ne843TrapDesc, ne843TrapSev, ne843TrapTime, ne843TrapDate, ne843TrapPath }
STATUS      current
DESCRIPTION
        "Generator Start"
 ::= { ne843Trap  110 }

ne843TrapIvp1Ilvi   NOTIFICATION-TYPE
OBJECTS     { ne843TrapDesc, ne843TrapSev, ne843TrapTime, ne843TrapDate, ne843TrapPath }
STATUS      current
DESCRIPTION
        "Inverter Low Input"
 ::= { ne843Trap  111 }

ne843TrapIvp1Ihvi   NOTIFICATION-TYPE
OBJECTS     { ne843TrapDesc, ne843TrapSev, ne843TrapTime, ne843TrapDate, ne843TrapPath }
STATUS      current
DESCRIPTION
        "Inverter High Input"
 ::= { ne843Trap  112 }

ne843TrapIvp1Ita   NOTIFICATION-TYPE
OBJECTS     { ne843TrapDesc, ne843TrapSev, ne843TrapTime, ne843TrapDate, ne843TrapPath }
STATUS      current
DESCRIPTION
        "Inverter High Temperature"
 ::= { ne843Trap  113 }

ne843TrapIvp1If   NOTIFICATION-TYPE
OBJECTS     { ne843TrapDesc, ne843TrapSev, ne843TrapTime, ne843TrapDate, ne843TrapPath }
STATUS      current
DESCRIPTION
        "Inverter Fail"
 ::= { ne843Trap  114 }

ne843TrapIvp1Ilv   NOTIFICATION-TYPE
OBJECTS     { ne843TrapDesc, ne843TrapSev, ne843TrapTime, ne843TrapDate, ne843TrapPath }
STATUS      current
DESCRIPTION
        "Inverter Low Output"
 ::= { ne843Trap  115 }

ne843TrapIvp1Ifa   NOTIFICATION-TYPE
OBJECTS     { ne843TrapDesc, ne843TrapSev, ne843TrapTime, ne843TrapDate, ne843TrapPath }
STATUS      current
DESCRIPTION
        "Inverter Frequency Lock"
 ::= { ne843Trap  116 }

ne843TrapIvp1Ihv   NOTIFICATION-TYPE
OBJECTS     { ne843TrapDesc, ne843TrapSev, ne843TrapTime, ne843TrapDate, ne843TrapPath }
STATUS      current
DESCRIPTION
        "Inverter High Output"
 ::= { ne843Trap  117 }

ne843TrapIvp1Ida   NOTIFICATION-TYPE
OBJECTS     { ne843TrapDesc, ne843TrapSev, ne843TrapTime, ne843TrapDate, ne843TrapPath }
STATUS      current
DESCRIPTION
        "Inverter Distribution Alarm"
 ::= { ne843Trap  118 }

ne843TrapIvp1Iof   NOTIFICATION-TYPE
OBJECTS     { ne843TrapDesc, ne843TrapSev, ne843TrapTime, ne843TrapDate, ne843TrapPath }
STATUS      current
DESCRIPTION
        "Inverter Output Fuse"
 ::= { ne843Trap  119 }

ne843TrapIvp1Idid   NOTIFICATION-TYPE
OBJECTS     { ne843TrapDesc, ne843TrapSev, ne843TrapTime, ne843TrapDate, ne843TrapPath }
STATUS      current
DESCRIPTION
        "Inverter ID Conflict"
 ::= { ne843Trap  120 }

ne843TrapIvp1Iirm   NOTIFICATION-TYPE
OBJECTS     { ne843TrapDesc, ne843TrapSev, ne843TrapTime, ne843TrapDate, ne843TrapPath }
STATUS      current
DESCRIPTION
        "Inverter High RMS Current"
 ::= { ne843Trap  121 }

ne843TrapIvp1Iipk   NOTIFICATION-TYPE
OBJECTS     { ne843TrapDesc, ne843TrapSev, ne843TrapTime, ne843TrapDate, ne843TrapPath }
STATUS      current
DESCRIPTION
        "Inverter High Peak Current"
 ::= { ne843Trap  122 }

ne843TrapIvp1Icf   NOTIFICATION-TYPE
OBJECTS     { ne843TrapDesc, ne843TrapSev, ne843TrapTime, ne843TrapDate, ne843TrapPath }
STATUS      current
DESCRIPTION
        "Inverter High Crest Factor"
 ::= { ne843Trap  123 }

ne843TrapIvp1Mif   NOTIFICATION-TYPE
OBJECTS     { ne843TrapDesc, ne843TrapSev, ne843TrapTime, ne843TrapDate, ne843TrapPath }
STATUS      current
DESCRIPTION
        "Multiple Inverter Fail"
 ::= { ne843Trap  124 }

ne843TrapIvp1Irls   NOTIFICATION-TYPE
OBJECTS     { ne843TrapDesc, ne843TrapSev, ne843TrapTime, ne843TrapDate, ne843TrapPath }
STATUS      current
DESCRIPTION
        "Inverter Redundancy Loss"
 ::= { ne843Trap  125 }

ne843TrapDc1Pmf   NOTIFICATION-TYPE
OBJECTS     { ne843TrapDesc, ne843TrapSev, ne843TrapTime, ne843TrapDate, ne843TrapPath }
STATUS      current
DESCRIPTION
        "Probe Minimum Fail"
 ::= { ne843Trap  126 }

ne843TrapPs1Crt   NOTIFICATION-TYPE
OBJECTS     { ne843TrapDesc, ne843TrapSev, ne843TrapTime, ne843TrapDate, ne843TrapPath }
STATUS      current
DESCRIPTION
        "Configuration Changed Reboot Required"
 ::= { ne843Trap  127 }

ne843TrapIvp1Milv   NOTIFICATION-TYPE
OBJECTS     { ne843TrapDesc, ne843TrapSev, ne843TrapTime, ne843TrapDate, ne843TrapPath }
STATUS      current
DESCRIPTION
        "Multiple Inverter Low Input Voltage"
 ::= { ne843Trap  128 }

ne843TrapDc1Faja   NOTIFICATION-TYPE
OBJECTS     { ne843TrapDesc, ne843TrapSev, ne843TrapTime, ne843TrapDate, ne843TrapPath }
STATUS      current
DESCRIPTION
        "Distribution Fuse A"
 ::= { ne843Trap  129 }

ne843TrapDc1Buht   NOTIFICATION-TYPE
OBJECTS     { ne843TrapDesc, ne843TrapSev, ne843TrapTime, ne843TrapDate, ne843TrapPath }
STATUS      current
DESCRIPTION
        "Bus Hi Temp"
 ::= { ne843Trap  130 }

ne843TrapDc1Buvht   NOTIFICATION-TYPE
OBJECTS     { ne843TrapDesc, ne843TrapSev, ne843TrapTime, ne843TrapDate, ne843TrapPath }
STATUS      current
DESCRIPTION
        "Bus Very Hi Temp"
 ::= { ne843Trap  131 }

ne843TrapDc1Btha   NOTIFICATION-TYPE
OBJECTS     { ne843TrapDesc, ne843TrapSev, ne843TrapTime, ne843TrapDate, ne843TrapPath }
STATUS      current
DESCRIPTION
        "Batt Hi Temp"
 ::= { ne843Trap  132 }

ne843TrapDc1Btvh   NOTIFICATION-TYPE
OBJECTS     { ne843TrapDesc, ne843TrapSev, ne843TrapTime, ne843TrapDate, ne843TrapPath }
STATUS      current
DESCRIPTION
        "Batt Very Hi Temp"
 ::= { ne843Trap  133 }

ne843TrapDc1Btla   NOTIFICATION-TYPE
OBJECTS     { ne843TrapDesc, ne843TrapSev, ne843TrapTime, ne843TrapDate, ne843TrapPath }
STATUS      current
DESCRIPTION
        "Batt Low Temp"
 ::= { ne843Trap  134 }

ne843TrapDc1Btvl   NOTIFICATION-TYPE
OBJECTS     { ne843TrapDesc, ne843TrapSev, ne843TrapTime, ne843TrapDate, ne843TrapPath }
STATUS      current
DESCRIPTION
        "Batt Very Low Temp"
 ::= { ne843Trap  135 }

ne843TrapDc1Laht   NOTIFICATION-TYPE
OBJECTS     { ne843TrapDesc, ne843TrapSev, ne843TrapTime, ne843TrapDate, ne843TrapPath }
STATUS      current
DESCRIPTION
        "Local Amb. Hi Temp"
 ::= { ne843Trap  136 }

ne843TrapDc1Lalt   NOTIFICATION-TYPE
OBJECTS     { ne843TrapDesc, ne843TrapSev, ne843TrapTime, ne843TrapDate, ne843TrapPath }
STATUS      current
DESCRIPTION
        "Local Amb. Low Temp"
 ::= { ne843Trap  137 }

ne843TrapDc1Raht   NOTIFICATION-TYPE
OBJECTS     { ne843TrapDesc, ne843TrapSev, ne843TrapTime, ne843TrapDate, ne843TrapPath }
STATUS      current
DESCRIPTION
        "Remote Amb. Hi Temp"
 ::= { ne843Trap  138 }

ne843TrapDc1Ravht   NOTIFICATION-TYPE
OBJECTS     { ne843TrapDesc, ne843TrapSev, ne843TrapTime, ne843TrapDate, ne843TrapPath }
STATUS      current
DESCRIPTION
        "Remote Amb. Very Hi Temp"
 ::= { ne843Trap  139 }

ne843TrapDc1Ralt   NOTIFICATION-TYPE
OBJECTS     { ne843TrapDesc, ne843TrapSev, ne843TrapTime, ne843TrapDate, ne843TrapPath }
STATUS      current
DESCRIPTION
        "Remote Amb. Low Temp"
 ::= { ne843Trap  140 }

ne843TrapDc1Vlva   NOTIFICATION-TYPE
OBJECTS     { ne843TrapDesc, ne843TrapSev, ne843TrapTime, ne843TrapDate, ne843TrapPath }
STATUS      current
DESCRIPTION
        "VA Power Loss"
 ::= { ne843Trap  141 }

ne843TrapDc1Vlvb   NOTIFICATION-TYPE
OBJECTS     { ne843TrapDesc, ne843TrapSev, ne843TrapTime, ne843TrapDate, ne843TrapPath }
STATUS      current
DESCRIPTION
        "VB Power Loss"
 ::= { ne843Trap  142 }

ne843TrapDc1Ovla   NOTIFICATION-TYPE
OBJECTS     { ne843TrapDesc, ne843TrapSev, ne843TrapTime, ne843TrapDate, ne843TrapPath }
STATUS      current
DESCRIPTION
        "IA Overload"
 ::= { ne843Trap  143 }

ne843TrapDc1Ovlb   NOTIFICATION-TYPE
OBJECTS     { ne843TrapDesc, ne843TrapSev, ne843TrapTime, ne843TrapDate, ne843TrapPath }
STATUS      current
DESCRIPTION
        "IB Overload"
 ::= { ne843Trap  144 }

ne843TrapDc1Pcaux   NOTIFICATION-TYPE
OBJECTS     { ne843TrapDesc, ne843TrapSev, ne843TrapTime, ne843TrapDate, ne843TrapPath }
STATUS      current
DESCRIPTION
        "PIC Auxiliary"
 ::= { ne843Trap  145 }

ne843TrapDc1Slot   NOTIFICATION-TYPE
OBJECTS     { ne843TrapDesc, ne843TrapSev, ne843TrapTime, ne843TrapDate, ne843TrapPath }
STATUS      current
DESCRIPTION
        "PIC Slot"
 ::= { ne843Trap  146 }

ne843TrapDc1Fajb   NOTIFICATION-TYPE
OBJECTS     { ne843TrapDesc, ne843TrapSev, ne843TrapTime, ne843TrapDate, ne843TrapPath }
STATUS      current
DESCRIPTION
        "Distribution Fuse B"
 ::= { ne843Trap  147 }

ne843TrapDc1Smw   NOTIFICATION-TYPE
OBJECTS     { ne843TrapDesc, ne843TrapSev, ne843TrapTime, ne843TrapDate, ne843TrapPath }
STATUS      current
DESCRIPTION
        "Shunt Mis-wired"
 ::= { ne843Trap  148 }

ne843TrapDc1Cca   NOTIFICATION-TYPE
OBJECTS     { ne843TrapDesc, ne843TrapSev, ne843TrapTime, ne843TrapDate, ne843TrapPath }
STATUS      current
DESCRIPTION
        "Circuit Assignment"
 ::= { ne843Trap  149 }

--
-- object ne843Retire
--

ne843Retire OBJECT IDENTIFIER  ::= { ne843  37 }


ne843RetireDc1Amj   NOTIFICATION-TYPE
OBJECTS     { ne843TrapDesc, ne843TrapSev, ne843TrapTime, ne843TrapDate, ne843TrapPath }
STATUS      current
DESCRIPTION
        "Auxiliary Fuse Major"
 ::= { ne843Retire  1 }

ne843RetireDc1Vsf   NOTIFICATION-TYPE
OBJECTS     { ne843TrapDesc, ne843TrapSev, ne843TrapTime, ne843TrapDate, ne843TrapPath }
STATUS      current
DESCRIPTION
        "Sense/Control Fuse"
 ::= { ne843Retire  2 }

ne843RetireDc1Osa   NOTIFICATION-TYPE
OBJECTS     { ne843TrapDesc, ne843TrapSev, ne843TrapTime, ne843TrapDate, ne843TrapPath }
STATUS      current
DESCRIPTION
        "Open String"
 ::= { ne843Retire  3 }

ne843RetireDc1Zid   NOTIFICATION-TYPE
OBJECTS     { ne843TrapDesc, ne843TrapSev, ne843TrapTime, ne843TrapDate, ne843TrapPath }
STATUS      current
DESCRIPTION
        "ID Not Configured"
 ::= { ne843Retire  4 }

ne843RetireDc1Tpa   NOTIFICATION-TYPE
OBJECTS     { ne843TrapDesc, ne843TrapSev, ne843TrapTime, ne843TrapDate, ne843TrapPath }
STATUS      current
DESCRIPTION
        "Thermal Probe Alarm"
 ::= { ne843Retire  5 }

ne843RetireDc1Vmf   NOTIFICATION-TYPE
OBJECTS     { ne843TrapDesc, ne843TrapSev, ne843TrapTime, ne843TrapDate, ne843TrapPath }
STATUS      current
DESCRIPTION
        "Voltage Module Fail"
 ::= { ne843Retire  6 }

ne843RetireDc1Cma   NOTIFICATION-TYPE
OBJECTS     { ne843TrapDesc, ne843TrapSev, ne843TrapTime, ne843TrapDate, ne843TrapPath }
STATUS      current
DESCRIPTION
        "Minor Communication Failure"
 ::= { ne843Retire  7 }

ne843RetireDc1Mcm   NOTIFICATION-TYPE
OBJECTS     { ne843TrapDesc, ne843TrapSev, ne843TrapTime, ne843TrapDate, ne843TrapPath }
STATUS      current
DESCRIPTION
        "Major Communication Failure"
 ::= { ne843Retire  8 }

ne843RetireDc1Epo   NOTIFICATION-TYPE
OBJECTS     { ne843TrapDesc, ne843TrapSev, ne843TrapTime, ne843TrapDate, ne843TrapPath }
STATUS      current
DESCRIPTION
        "Emergency Power Off"
 ::= { ne843Retire  9 }

ne843RetireDc1Icr   NOTIFICATION-TYPE
OBJECTS     { ne843TrapDesc, ne843TrapSev, ne843TrapTime, ne843TrapDate, ne843TrapPath }
STATUS      current
DESCRIPTION
        "Incompatible Rectifier"
 ::= { ne843Retire  10 }

ne843RetireDc1Rfa   NOTIFICATION-TYPE
OBJECTS     { ne843TrapDesc, ne843TrapSev, ne843TrapTime, ne843TrapDate, ne843TrapPath }
STATUS      current
DESCRIPTION
        "Rectifier Fail"
 ::= { ne843Retire  11 }

ne843RetireDc1Acf   NOTIFICATION-TYPE
OBJECTS     { ne843TrapDesc, ne843TrapSev, ne843TrapTime, ne843TrapDate, ne843TrapPath }
STATUS      current
DESCRIPTION
        "AC Fail"
 ::= { ne843Retire  12 }

ne843RetireDc1Man   NOTIFICATION-TYPE
OBJECTS     { ne843TrapDesc, ne843TrapSev, ne843TrapTime, ne843TrapDate, ne843TrapPath }
STATUS      current
DESCRIPTION
        "Manual Off"
 ::= { ne843Retire  13 }

ne843RetireDc1Did   NOTIFICATION-TYPE
OBJECTS     { ne843TrapDesc, ne843TrapSev, ne843TrapTime, ne843TrapDate, ne843TrapPath }
STATUS      current
DESCRIPTION
        "ID Conflict"
 ::= { ne843Retire  14 }

ne843RetireDc1Clm   NOTIFICATION-TYPE
OBJECTS     { ne843TrapDesc, ne843TrapSev, ne843TrapTime, ne843TrapDate, ne843TrapPath }
STATUS      current
DESCRIPTION
        "Rectifier Current Limit"
 ::= { ne843Retire  15 }

ne843RetireDc1Rfn   NOTIFICATION-TYPE
OBJECTS     { ne843TrapDesc, ne843TrapSev, ne843TrapTime, ne843TrapDate, ne843TrapPath }
STATUS      current
DESCRIPTION
        "Rectifier Fan Failure"
 ::= { ne843Retire  16 }

ne843RetireDc1Vla   NOTIFICATION-TYPE
OBJECTS     { ne843TrapDesc, ne843TrapSev, ne843TrapTime, ne843TrapDate, ne843TrapPath }
STATUS      current
DESCRIPTION
        "Very Low Voltage"
 ::= { ne843Retire  17 }

ne843RetireDc1Mfa   NOTIFICATION-TYPE
OBJECTS     { ne843TrapDesc, ne843TrapSev, ne843TrapTime, ne843TrapDate, ne843TrapPath }
STATUS      current
DESCRIPTION
        "Multiple Rectifier Fail"
 ::= { ne843Retire  18 }

ne843RetireDc1Rtl   NOTIFICATION-TYPE
OBJECTS     { ne843TrapDesc, ne843TrapSev, ne843TrapTime, ne843TrapDate, ne843TrapPath }
STATUS      current
DESCRIPTION
        "Reserve Time Low"
 ::= { ne843Retire  19 }

ne843RetireDc1Rrtl   NOTIFICATION-TYPE
OBJECTS     { ne843TrapDesc, ne843TrapSev, ne843TrapTime, ne843TrapDate, ne843TrapPath }
STATUS      current
DESCRIPTION
        "Real-time Reserve Time Low"
 ::= { ne843Retire  20 }

ne843RetireDc1Rls   NOTIFICATION-TYPE
OBJECTS     { ne843TrapDesc, ne843TrapSev, ne843TrapTime, ne843TrapDate, ne843TrapPath }
STATUS      current
DESCRIPTION
        "Redundancy Loss"
 ::= { ne843Retire  21 }

ne843RetireDc1Mman   NOTIFICATION-TYPE
OBJECTS     { ne843TrapDesc, ne843TrapSev, ne843TrapTime, ne843TrapDate, ne843TrapPath }
STATUS      current
DESCRIPTION
        "Multiple Manual Off"
 ::= { ne843Retire  22 }

ne843RetireDc1Macf   NOTIFICATION-TYPE
OBJECTS     { ne843TrapDesc, ne843TrapSev, ne843TrapTime, ne843TrapDate, ne843TrapPath }
STATUS      current
DESCRIPTION
        "Multiple AC Failure"
 ::= { ne843Retire  23 }

ne843RetireDc1Bda   NOTIFICATION-TYPE
OBJECTS     { ne843TrapDesc, ne843TrapSev, ne843TrapTime, ne843TrapDate, ne843TrapPath }
STATUS      current
DESCRIPTION
        "Battery On Discharge"
 ::= { ne843Retire  24 }

ne843RetireDc1Hva   NOTIFICATION-TYPE
OBJECTS     { ne843TrapDesc, ne843TrapSev, ne843TrapTime, ne843TrapDate, ne843TrapPath }
STATUS      current
DESCRIPTION
        "High Voltage"
 ::= { ne843Retire  25 }

ne843RetireDc1Hfv   NOTIFICATION-TYPE
OBJECTS     { ne843TrapDesc, ne843TrapSev, ne843TrapTime, ne843TrapDate, ne843TrapPath }
STATUS      current
DESCRIPTION
        "High Float Voltage"
 ::= { ne843Retire  26 }

ne843RetirePs1Epr   NOTIFICATION-TYPE
OBJECTS     { ne843TrapDesc, ne843TrapSev, ne843TrapTime, ne843TrapDate, ne843TrapPath }
STATUS      current
DESCRIPTION
        "External Password Reset"
 ::= { ne843Retire  27 }

ne843RetirePs1Pfd   NOTIFICATION-TYPE
OBJECTS     { ne843TrapDesc, ne843TrapSev, ne843TrapTime, ne843TrapDate, ne843TrapPath }
STATUS      current
DESCRIPTION
        "Passwords At Default"
 ::= { ne843Retire  28 }

ne843RetirePs1Exl   NOTIFICATION-TYPE
OBJECTS     { ne843TrapDesc, ne843TrapSev, ne843TrapTime, ne843TrapDate, ne843TrapPath }
STATUS      current
DESCRIPTION
        "Excessive Login Attempts"
 ::= { ne843Retire  29 }

ne843RetirePs1Bbl   NOTIFICATION-TYPE
OBJECTS     { ne843TrapDesc, ne843TrapSev, ne843TrapTime, ne843TrapDate, ne843TrapPath }
STATUS      current
DESCRIPTION
        "Memory Backup Battery Low"
 ::= { ne843Retire  30 }

ne843RetirePs1Clc   NOTIFICATION-TYPE
OBJECTS     { ne843TrapDesc, ne843TrapSev, ne843TrapTime, ne843TrapDate, ne843TrapPath }
STATUS      current
DESCRIPTION
        "Clock Changed"
 ::= { ne843Retire  31 }

ne843RetirePs1Stf   NOTIFICATION-TYPE
OBJECTS     { ne843TrapDesc, ne843TrapSev, ne843TrapTime, ne843TrapDate, ne843TrapPath }
STATUS      current
DESCRIPTION
        "Self Test Failed"
 ::= { ne843Retire  32 }

ne843RetirePs1Pgi   NOTIFICATION-TYPE
OBJECTS     { ne843TrapDesc, ne843TrapSev, ne843TrapTime, ne843TrapDate, ne843TrapPath }
STATUS      current
DESCRIPTION
        "Program Line Invalid"
 ::= { ne843Retire  33 }

ne843RetirePs1Cch   NOTIFICATION-TYPE
OBJECTS     { ne843TrapDesc, ne843TrapSev, ne843TrapTime, ne843TrapDate, ne843TrapPath }
STATUS      current
DESCRIPTION
        "Configuration Changed"
 ::= { ne843Retire  34 }

ne843RetirePs1Hcl   NOTIFICATION-TYPE
OBJECTS     { ne843TrapDesc, ne843TrapSev, ne843TrapTime, ne843TrapDate, ne843TrapPath }
STATUS      current
DESCRIPTION
        "History Cleared"
 ::= { ne843Retire  35 }

ne843RetirePs1Ax1   NOTIFICATION-TYPE
OBJECTS     { ne843TrapDesc, ne843TrapSev, ne843TrapTime, ne843TrapDate, ne843TrapPath }
STATUS      current
DESCRIPTION
        "Auxiliary Event 1"
 ::= { ne843Retire  36 }

ne843RetirePs1Ax2   NOTIFICATION-TYPE
OBJECTS     { ne843TrapDesc, ne843TrapSev, ne843TrapTime, ne843TrapDate, ne843TrapPath }
STATUS      current
DESCRIPTION
        "Auxiliary Event 2"
 ::= { ne843Retire  37 }

ne843RetirePs1Ax3   NOTIFICATION-TYPE
OBJECTS     { ne843TrapDesc, ne843TrapSev, ne843TrapTime, ne843TrapDate, ne843TrapPath }
STATUS      current
DESCRIPTION
        "Auxiliary Event 3"
 ::= { ne843Retire  38 }

ne843RetirePs1Ax4   NOTIFICATION-TYPE
OBJECTS     { ne843TrapDesc, ne843TrapSev, ne843TrapTime, ne843TrapDate, ne843TrapPath }
STATUS      current
DESCRIPTION
        "Auxiliary Event 4"
 ::= { ne843Retire  39 }

ne843RetirePs1Ax5   NOTIFICATION-TYPE
OBJECTS     { ne843TrapDesc, ne843TrapSev, ne843TrapTime, ne843TrapDate, ne843TrapPath }
STATUS      current
DESCRIPTION
        "Auxiliary Event 5"
 ::= { ne843Retire  40 }

ne843RetirePs1Ax6   NOTIFICATION-TYPE
OBJECTS     { ne843TrapDesc, ne843TrapSev, ne843TrapTime, ne843TrapDate, ne843TrapPath }
STATUS      current
DESCRIPTION
        "Auxiliary Event 6"
 ::= { ne843Retire  41 }

ne843RetirePs1Fan24   NOTIFICATION-TYPE
OBJECTS     { ne843TrapDesc, ne843TrapSev, ne843TrapTime, ne843TrapDate, ne843TrapPath }
STATUS      current
DESCRIPTION
        "24 V Fuse Minor"
 ::= { ne843Retire  42 }

ne843RetirePs1Fan48   NOTIFICATION-TYPE
OBJECTS     { ne843TrapDesc, ne843TrapSev, ne843TrapTime, ne843TrapDate, ne843TrapPath }
STATUS      current
DESCRIPTION
        "48 V Fuse Minor"
 ::= { ne843Retire  43 }

ne843RetirePs1Faj24   NOTIFICATION-TYPE
OBJECTS     { ne843TrapDesc, ne843TrapSev, ne843TrapTime, ne843TrapDate, ne843TrapPath }
STATUS      current
DESCRIPTION
        "24 V Fuse Major"
 ::= { ne843Retire  44 }

ne843RetirePs1Faj48   NOTIFICATION-TYPE
OBJECTS     { ne843TrapDesc, ne843TrapSev, ne843TrapTime, ne843TrapDate, ne843TrapPath }
STATUS      current
DESCRIPTION
        "48 V Fuse Major"
 ::= { ne843Retire  45 }

ne843RetireAt1Ata   NOTIFICATION-TYPE
OBJECTS     { ne843TrapDesc, ne843TrapSev, ne843TrapTime, ne843TrapDate, ne843TrapPath }
STATUS      current
DESCRIPTION
        "Alarm Test Active"
 ::= { ne843Retire  46 }

ne843RetireAt1Atb   NOTIFICATION-TYPE
OBJECTS     { ne843TrapDesc, ne843TrapSev, ne843TrapTime, ne843TrapDate, ne843TrapPath }
STATUS      current
DESCRIPTION
        "Alarm Test Aborted"
 ::= { ne843Retire  47 }

ne843RetireCp1Cfa   NOTIFICATION-TYPE
OBJECTS     { ne843TrapDesc, ne843TrapSev, ne843TrapTime, ne843TrapDate, ne843TrapPath }
STATUS      current
DESCRIPTION
        "Converter Fail"
 ::= { ne843Retire  48 }

ne843RetireCp1Cfn   NOTIFICATION-TYPE
OBJECTS     { ne843TrapDesc, ne843TrapSev, ne843TrapTime, ne843TrapDate, ne843TrapPath }
STATUS      current
DESCRIPTION
        "Converter Fan Minor"
 ::= { ne843Retire  49 }

ne843RetireCp1Cfj   NOTIFICATION-TYPE
OBJECTS     { ne843TrapDesc, ne843TrapSev, ne843TrapTime, ne843TrapDate, ne843TrapPath }
STATUS      current
DESCRIPTION
        "Converter Fan Major"
 ::= { ne843Retire  50 }

ne843RetireCp1Dfa   NOTIFICATION-TYPE
OBJECTS     { ne843TrapDesc, ne843TrapSev, ne843TrapTime, ne843TrapDate, ne843TrapPath }
STATUS      current
DESCRIPTION
        "Distribution Fail"
 ::= { ne843Retire  51 }

ne843RetireCp1Did   NOTIFICATION-TYPE
OBJECTS     { ne843TrapDesc, ne843TrapSev, ne843TrapTime, ne843TrapDate, ne843TrapPath }
STATUS      current
DESCRIPTION
        "ID Conflict"
 ::= { ne843Retire  52 }

ne843RetireCp1Icc   NOTIFICATION-TYPE
OBJECTS     { ne843TrapDesc, ne843TrapSev, ne843TrapTime, ne843TrapDate, ne843TrapPath }
STATUS      current
DESCRIPTION
        "Incompatible Converter Alarm"
 ::= { ne843Retire  53 }

ne843RetireCp1Mfa   NOTIFICATION-TYPE
OBJECTS     { ne843TrapDesc, ne843TrapSev, ne843TrapTime, ne843TrapDate, ne843TrapPath }
STATUS      current
DESCRIPTION
        "Multiple Converter Fail"
 ::= { ne843Retire  54 }

ne843RetireCp1Hva   NOTIFICATION-TYPE
OBJECTS     { ne843TrapDesc, ne843TrapSev, ne843TrapTime, ne843TrapDate, ne843TrapPath }
STATUS      current
DESCRIPTION
        "Converter High Voltage Major"
 ::= { ne843Retire  55 }

ne843RetireCp1Hfv   NOTIFICATION-TYPE
OBJECTS     { ne843TrapDesc, ne843TrapSev, ne843TrapTime, ne843TrapDate, ne843TrapPath }
STATUS      current
DESCRIPTION
        "Converter High Voltage Minor"
 ::= { ne843Retire  56 }

ne843RetireCp1Vla   NOTIFICATION-TYPE
OBJECTS     { ne843TrapDesc, ne843TrapSev, ne843TrapTime, ne843TrapDate, ne843TrapPath }
STATUS      current
DESCRIPTION
        "Converter Very Low Voltage"
 ::= { ne843Retire  57 }

ne843RetireCp1Rl   NOTIFICATION-TYPE
OBJECTS     { ne843TrapDesc, ne843TrapSev, ne843TrapTime, ne843TrapDate, ne843TrapPath }
STATUS      current
DESCRIPTION
        "Converter Redundancy Loss"
 ::= { ne843Retire  58 }

ne843RetireBr1Bta   NOTIFICATION-TYPE
OBJECTS     { ne843TrapDesc, ne843TrapSev, ne843TrapTime, ne843TrapDate, ne843TrapPath }
STATUS      current
DESCRIPTION
        "Battery Test Active"
 ::= { ne843Retire  59 }

ne843RetireBr1Bfa   NOTIFICATION-TYPE
OBJECTS     { ne843TrapDesc, ne843TrapSev, ne843TrapTime, ne843TrapDate, ne843TrapPath }
STATUS      current
DESCRIPTION
        "Battery Test Failed"
 ::= { ne843Retire  60 }

ne843RetireBr1Scda   NOTIFICATION-TYPE
OBJECTS     { ne843TrapDesc, ne843TrapSev, ne843TrapTime, ne843TrapDate, ne843TrapPath }
STATUS      current
DESCRIPTION
        "Shorted Cell Detected"
 ::= { ne843Retire  61 }

ne843RetireBr1Isda   NOTIFICATION-TYPE
OBJECTS     { ne843TrapDesc, ne843TrapSev, ne843TrapTime, ne843TrapDate, ne843TrapPath }
STATUS      current
DESCRIPTION
        "Imminent Shutdown"
 ::= { ne843Retire  62 }

ne843RetireBr1Mdp   NOTIFICATION-TYPE
OBJECTS     { ne843TrapDesc, ne843TrapSev, ne843TrapTime, ne843TrapDate, ne843TrapPath }
STATUS      current
DESCRIPTION
        "Voltage Duplicate ID"
 ::= { ne843Retire  63 }

ne843RetireBr1Mzd   NOTIFICATION-TYPE
OBJECTS     { ne843TrapDesc, ne843TrapSev, ne843TrapTime, ne843TrapDate, ne843TrapPath }
STATUS      current
DESCRIPTION
        "Voltage ID Not Configured"
 ::= { ne843Retire  64 }

ne843RetireBr1Btha   NOTIFICATION-TYPE
OBJECTS     { ne843TrapDesc, ne843TrapSev, ne843TrapTime, ne843TrapDate, ne843TrapPath }
STATUS      current
DESCRIPTION
        "High Battery Temperature"
 ::= { ne843Retire  65 }

ne843RetireCn1Cno   NOTIFICATION-TYPE
OBJECTS     { ne843TrapDesc, ne843TrapSev, ne843TrapTime, ne843TrapDate, ne843TrapPath }
STATUS      current
DESCRIPTION
        "Contactor Open"
 ::= { ne843Retire  66 }

ne843RetireCn1Cnf   NOTIFICATION-TYPE
OBJECTS     { ne843TrapDesc, ne843TrapSev, ne843TrapTime, ne843TrapDate, ne843TrapPath }
STATUS      current
DESCRIPTION
        "Contactor Failed"
 ::= { ne843Retire  67 }

ne843RetireCn2Cno   NOTIFICATION-TYPE
OBJECTS     { ne843TrapDesc, ne843TrapSev, ne843TrapTime, ne843TrapDate, ne843TrapPath }
STATUS      current
DESCRIPTION
        "Contactor Open"
 ::= { ne843Retire  68 }

ne843RetireCn2Cnf   NOTIFICATION-TYPE
OBJECTS     { ne843TrapDesc, ne843TrapSev, ne843TrapTime, ne843TrapDate, ne843TrapPath }
STATUS      current
DESCRIPTION
        "Contactor Failed"
 ::= { ne843Retire  69 }

ne843RetireCn3Cno   NOTIFICATION-TYPE
OBJECTS     { ne843TrapDesc, ne843TrapSev, ne843TrapTime, ne843TrapDate, ne843TrapPath }
STATUS      current
DESCRIPTION
        "Contactor Open"
 ::= { ne843Retire  70 }

ne843RetireCn3Cnf   NOTIFICATION-TYPE
OBJECTS     { ne843TrapDesc, ne843TrapSev, ne843TrapTime, ne843TrapDate, ne843TrapPath }
STATUS      current
DESCRIPTION
        "Contactor Failed"
 ::= { ne843Retire  71 }

ne843RetireCn4Cno   NOTIFICATION-TYPE
OBJECTS     { ne843TrapDesc, ne843TrapSev, ne843TrapTime, ne843TrapDate, ne843TrapPath }
STATUS      current
DESCRIPTION
        "Contactor Open"
 ::= { ne843Retire  72 }

ne843RetireCn4Cnf   NOTIFICATION-TYPE
OBJECTS     { ne843TrapDesc, ne843TrapSev, ne843TrapTime, ne843TrapDate, ne843TrapPath }
STATUS      current
DESCRIPTION
        "Contactor Failed"
 ::= { ne843Retire  73 }

ne843RetireCm1Cof   NOTIFICATION-TYPE
OBJECTS     { ne843TrapDesc, ne843TrapSev, ne843TrapTime, ne843TrapDate, ne843TrapPath }
STATUS      current
DESCRIPTION
        "Queue Overflow"
 ::= { ne843Retire  74 }

ne843RetireCm1Cor   NOTIFICATION-TYPE
OBJECTS     { ne843TrapDesc, ne843TrapSev, ne843TrapTime, ne843TrapDate, ne843TrapPath }
STATUS      current
DESCRIPTION
        "Number Did Not Respond"
 ::= { ne843Retire  75 }

ne843RetireCm1Nnc   NOTIFICATION-TYPE
OBJECTS     { ne843TrapDesc, ne843TrapSev, ne843TrapTime, ne843TrapDate, ne843TrapPath }
STATUS      current
DESCRIPTION
        "Number Not Configured"
 ::= { ne843Retire  76 }

ne843RetirePo1Por   NOTIFICATION-TYPE
OBJECTS     { ne843TrapDesc, ne843TrapSev, ne843TrapTime, ne843TrapDate, ne843TrapPath }
STATUS      current
DESCRIPTION
        "Number Did Not Respond"
 ::= { ne843Retire  77 }

ne843RetireRp1Rf   NOTIFICATION-TYPE
OBJECTS     { ne843TrapDesc, ne843TrapSev, ne843TrapTime, ne843TrapDate, ne843TrapPath }
STATUS      current
DESCRIPTION
        "Ringer Minor Fail"
 ::= { ne843Retire  78 }

ne843RetireRp1Rpff   NOTIFICATION-TYPE
OBJECTS     { ne843TrapDesc, ne843TrapSev, ne843TrapTime, ne843TrapDate, ne843TrapPath }
STATUS      current
DESCRIPTION
        "Ringer Fan Fail"
 ::= { ne843Retire  79 }

ne843RetireRp1Rprl   NOTIFICATION-TYPE
OBJECTS     { ne843TrapDesc, ne843TrapSev, ne843TrapTime, ne843TrapDate, ne843TrapPath }
STATUS      current
DESCRIPTION
        "Ringer Redundancy Loss"
 ::= { ne843Retire  80 }

ne843RetireRp1Rpfj   NOTIFICATION-TYPE
OBJECTS     { ne843TrapDesc, ne843TrapSev, ne843TrapTime, ne843TrapDate, ne843TrapPath }
STATUS      current
DESCRIPTION
        "Ringer Major Fail"
 ::= { ne843Retire  81 }

ne843RetireRp1Rpxj   NOTIFICATION-TYPE
OBJECTS     { ne843TrapDesc, ne843TrapSev, ne843TrapTime, ne843TrapDate, ne843TrapPath }
STATUS      current
DESCRIPTION
        "Ringer Major External Fault"
 ::= { ne843Retire  82 }

ne843RetireRp1Rpxn   NOTIFICATION-TYPE
OBJECTS     { ne843TrapDesc, ne843TrapSev, ne843TrapTime, ne843TrapDate, ne843TrapPath }
STATUS      current
DESCRIPTION
        "Ringer Minor External Fault"
 ::= { ne843Retire  83 }

ne843RetireRp1Rcdp   NOTIFICATION-TYPE
OBJECTS     { ne843TrapDesc, ne843TrapSev, ne843TrapTime, ne843TrapDate, ne843TrapPath }
STATUS      current
DESCRIPTION
        "Ringer ID Conflict"
 ::= { ne843Retire  84 }

ne843RetireUserDefined   NOTIFICATION-TYPE
OBJECTS     { ne843TrapDesc, ne843TrapSev, ne843TrapTime, ne843TrapDate, ne843TrapPath }
STATUS      current
DESCRIPTION
        "This may be a user defined event, or a new controller event."
 ::= { ne843Retire  85 }

ne843RetireDc1Emd   NOTIFICATION-TYPE
OBJECTS     { ne843TrapDesc, ne843TrapSev, ne843TrapTime, ne843TrapDate, ne843TrapPath }
STATUS      current
DESCRIPTION
        "Energy Management Disabled"
 ::= { ne843Retire  86 }

ne843RetireDc1Pfs   NOTIFICATION-TYPE
OBJECTS     { ne843TrapDesc, ne843TrapSev, ne843TrapTime, ne843TrapDate, ne843TrapPath }
STATUS      current
DESCRIPTION
        "Thermal Probe Fail Safe"
 ::= { ne843Retire  87 }

ne843RetireDc1Rif   NOTIFICATION-TYPE
OBJECTS     { ne843TrapDesc, ne843TrapSev, ne843TrapTime, ne843TrapDate, ne843TrapPath }
STATUS      current
DESCRIPTION
        "Rectifier Internal Fault"
 ::= { ne843Retire  88 }

ne843RetireDc1Lsf   NOTIFICATION-TYPE
OBJECTS     { ne843TrapDesc, ne843TrapSev, ne843TrapTime, ne843TrapDate, ne843TrapPath }
STATUS      current
DESCRIPTION
        "Load Share Fail"
 ::= { ne843Retire  89 }

ne843RetirePs1Ax7   NOTIFICATION-TYPE
OBJECTS     { ne843TrapDesc, ne843TrapSev, ne843TrapTime, ne843TrapDate, ne843TrapPath }
STATUS      current
DESCRIPTION
        "Auxiliary Event 7"
 ::= { ne843Retire  90 }

ne843RetirePs1Ax8   NOTIFICATION-TYPE
OBJECTS     { ne843TrapDesc, ne843TrapSev, ne843TrapTime, ne843TrapDate, ne843TrapPath }
STATUS      current
DESCRIPTION
        "Auxiliary Event 8"
 ::= { ne843Retire  91 }

ne843RetirePs1Ax9   NOTIFICATION-TYPE
OBJECTS     { ne843TrapDesc, ne843TrapSev, ne843TrapTime, ne843TrapDate, ne843TrapPath }
STATUS      current
DESCRIPTION
        "Auxiliary Event 9"
 ::= { ne843Retire  92 }

ne843RetirePs1Ax10   NOTIFICATION-TYPE
OBJECTS     { ne843TrapDesc, ne843TrapSev, ne843TrapTime, ne843TrapDate, ne843TrapPath }
STATUS      current
DESCRIPTION
        "Auxiliary Event 10"
 ::= { ne843Retire  93 }

ne843RetirePs1Ax11   NOTIFICATION-TYPE
OBJECTS     { ne843TrapDesc, ne843TrapSev, ne843TrapTime, ne843TrapDate, ne843TrapPath }
STATUS      current
DESCRIPTION
        "Auxiliary Event 11"
 ::= { ne843Retire  94 }

ne843RetirePs1Ax12   NOTIFICATION-TYPE
OBJECTS     { ne843TrapDesc, ne843TrapSev, ne843TrapTime, ne843TrapDate, ne843TrapPath }
STATUS      current
DESCRIPTION
        "Auxiliary Event 12"
 ::= { ne843Retire  95 }

ne843RetireBr1Btla   NOTIFICATION-TYPE
OBJECTS     { ne843TrapDesc, ne843TrapSev, ne843TrapTime, ne843TrapDate, ne843TrapPath }
STATUS      current
DESCRIPTION
        "Low Battery Temperature"
 ::= { ne843Retire  96 }

ne843RetireBr1Btvh   NOTIFICATION-TYPE
OBJECTS     { ne843TrapDesc, ne843TrapSev, ne843TrapTime, ne843TrapDate, ne843TrapPath }
STATUS      current
DESCRIPTION
        "Very High Battery Temperature"
 ::= { ne843Retire  97 }

ne843RetireBr1Btvl   NOTIFICATION-TYPE
OBJECTS     { ne843TrapDesc, ne843TrapSev, ne843TrapTime, ne843TrapDate, ne843TrapPath }
STATUS      current
DESCRIPTION
        "Very Low Battery Temperature"
 ::= { ne843Retire  98 }

ne843RetireGn1Gnr   NOTIFICATION-TYPE
OBJECTS     { ne843TrapDesc, ne843TrapSev, ne843TrapTime, ne843TrapDate, ne843TrapPath }
STATUS      current
DESCRIPTION
        "Generator Running"
 ::= { ne843Retire  99 }

ne843RetireGn1Gnm   NOTIFICATION-TYPE
OBJECTS     { ne843TrapDesc, ne843TrapSev, ne843TrapTime, ne843TrapDate, ne843TrapPath }
STATUS      current
DESCRIPTION
        "Generator Maintenance Required"
 ::= { ne843Retire  100 }

ne843RetireGn1Gnf   NOTIFICATION-TYPE
OBJECTS     { ne843TrapDesc, ne843TrapSev, ne843TrapTime, ne843TrapDate, ne843TrapPath }
STATUS      current
DESCRIPTION
        "Generator Fail"
 ::= { ne843Retire  101 }

ne843RetirePs1Amtl   NOTIFICATION-TYPE
OBJECTS     { ne843TrapDesc, ne843TrapSev, ne843TrapTime, ne843TrapDate, ne843TrapPath }
STATUS      current
DESCRIPTION
        "Low Ambient Temperature"
 ::= { ne843Retire  102 }

ne843RetirePs1Amth   NOTIFICATION-TYPE
OBJECTS     { ne843TrapDesc, ne843TrapSev, ne843TrapTime, ne843TrapDate, ne843TrapPath }
STATUS      current
DESCRIPTION
        "High Ambient Temperature"
 ::= { ne843Retire  103 }

ne843RetireAco1Aac   NOTIFICATION-TYPE
OBJECTS     { ne843TrapDesc, ne843TrapSev, ne843TrapTime, ne843TrapDate, ne843TrapPath }
STATUS      current
DESCRIPTION
        "ACO Active"
 ::= { ne843Retire  104 }

ne843RetireBr1Rba   NOTIFICATION-TYPE
OBJECTS     { ne843TrapDesc, ne843TrapSev, ne843TrapTime, ne843TrapDate, ne843TrapPath }
STATUS      current
DESCRIPTION
        "Reverse Battery"
 ::= { ne843Retire  105 }

ne843RetireCp1Cin   NOTIFICATION-TYPE
OBJECTS     { ne843TrapDesc, ne843TrapSev, ne843TrapTime, ne843TrapDate, ne843TrapPath }
STATUS      current
DESCRIPTION
        "Converter Input Fail"
 ::= { ne843Retire  106 }

ne843RetireDc1Bof   NOTIFICATION-TYPE
OBJECTS     { ne843TrapDesc, ne843TrapSev, ne843TrapTime, ne843TrapDate, ne843TrapPath }
STATUS      current
DESCRIPTION
        "Rectifier ORing FET Fault"
 ::= { ne843Retire  107 }

ne843RetireDc1Sof   NOTIFICATION-TYPE
OBJECTS     { ne843TrapDesc, ne843TrapSev, ne843TrapTime, ne843TrapDate, ne843TrapPath }
STATUS      current
DESCRIPTION
        "Rectifier Shorted ORing FET"
 ::= { ne843Retire  108 }

ne843RetireDc1Der   NOTIFICATION-TYPE
OBJECTS     { ne843TrapDesc, ne843TrapSev, ne843TrapTime, ne843TrapDate, ne843TrapPath }
STATUS      current
DESCRIPTION
        "Rectifier Under Voltage"
 ::= { ne843Retire  109 }

ne843RetireGn1Gns   NOTIFICATION-TYPE
OBJECTS     { ne843TrapDesc, ne843TrapSev, ne843TrapTime, ne843TrapDate, ne843TrapPath }
STATUS      current
DESCRIPTION
        "Generator Start"
 ::= { ne843Retire  110 }

ne843RetireIvp1Ilvi   NOTIFICATION-TYPE
OBJECTS     { ne843TrapDesc, ne843TrapSev, ne843TrapTime, ne843TrapDate, ne843TrapPath }
STATUS      current
DESCRIPTION
        "Inverter Low Input"
 ::= { ne843Retire  111 }

ne843RetireIvp1Ihvi   NOTIFICATION-TYPE
OBJECTS     { ne843TrapDesc, ne843TrapSev, ne843TrapTime, ne843TrapDate, ne843TrapPath }
STATUS      current
DESCRIPTION
        "Inverter High Input"
 ::= { ne843Retire  112 }

ne843RetireIvp1Ita   NOTIFICATION-TYPE
OBJECTS     { ne843TrapDesc, ne843TrapSev, ne843TrapTime, ne843TrapDate, ne843TrapPath }
STATUS      current
DESCRIPTION
        "Inverter High Temperature"
 ::= { ne843Retire  113 }

ne843RetireIvp1If   NOTIFICATION-TYPE
OBJECTS     { ne843TrapDesc, ne843TrapSev, ne843TrapTime, ne843TrapDate, ne843TrapPath }
STATUS      current
DESCRIPTION
        "Inverter Fail"
 ::= { ne843Retire  114 }

ne843RetireIvp1Ilv   NOTIFICATION-TYPE
OBJECTS     { ne843TrapDesc, ne843TrapSev, ne843TrapTime, ne843TrapDate, ne843TrapPath }
STATUS      current
DESCRIPTION
        "Inverter Low Output"
 ::= { ne843Retire  115 }

ne843RetireIvp1Ifa   NOTIFICATION-TYPE
OBJECTS     { ne843TrapDesc, ne843TrapSev, ne843TrapTime, ne843TrapDate, ne843TrapPath }
STATUS      current
DESCRIPTION
        "Inverter Frequency Lock"
 ::= { ne843Retire  116 }

ne843RetireIvp1Ihv   NOTIFICATION-TYPE
OBJECTS     { ne843TrapDesc, ne843TrapSev, ne843TrapTime, ne843TrapDate, ne843TrapPath }
STATUS      current
DESCRIPTION
        "Inverter High Output"
 ::= { ne843Retire  117 }

ne843RetireIvp1Ida   NOTIFICATION-TYPE
OBJECTS     { ne843TrapDesc, ne843TrapSev, ne843TrapTime, ne843TrapDate, ne843TrapPath }
STATUS      current
DESCRIPTION
        "Inverter Distribution Alarm"
 ::= { ne843Retire  118 }

ne843RetireIvp1Iof   NOTIFICATION-TYPE
OBJECTS     { ne843TrapDesc, ne843TrapSev, ne843TrapTime, ne843TrapDate, ne843TrapPath }
STATUS      current
DESCRIPTION
        "Inverter Output Fuse"
 ::= { ne843Retire  119 }

ne843RetireIvp1Idid   NOTIFICATION-TYPE
OBJECTS     { ne843TrapDesc, ne843TrapSev, ne843TrapTime, ne843TrapDate, ne843TrapPath }
STATUS      current
DESCRIPTION
        "Inverter ID Conflict"
 ::= { ne843Retire  120 }

ne843RetireIvp1Iirm   NOTIFICATION-TYPE
OBJECTS     { ne843TrapDesc, ne843TrapSev, ne843TrapTime, ne843TrapDate, ne843TrapPath }
STATUS      current
DESCRIPTION
        "Inverter High RMS Current"
 ::= { ne843Retire  121 }

ne843RetireIvp1Iipk   NOTIFICATION-TYPE
OBJECTS     { ne843TrapDesc, ne843TrapSev, ne843TrapTime, ne843TrapDate, ne843TrapPath }
STATUS      current
DESCRIPTION
        "Inverter High Peak Current"
 ::= { ne843Retire  122 }

ne843RetireIvp1Icf   NOTIFICATION-TYPE
OBJECTS     { ne843TrapDesc, ne843TrapSev, ne843TrapTime, ne843TrapDate, ne843TrapPath }
STATUS      current
DESCRIPTION
        "Inverter High Crest Factor"
 ::= { ne843Retire  123 }

ne843RetireIvp1Mif   NOTIFICATION-TYPE
OBJECTS     { ne843TrapDesc, ne843TrapSev, ne843TrapTime, ne843TrapDate, ne843TrapPath }
STATUS      current
DESCRIPTION
        "Multiple Inverter Fail"
 ::= { ne843Retire  124 }

ne843RetireIvp1Irls   NOTIFICATION-TYPE
OBJECTS     { ne843TrapDesc, ne843TrapSev, ne843TrapTime, ne843TrapDate, ne843TrapPath }
STATUS      current
DESCRIPTION
        "Inverter Redundancy Loss"
 ::= { ne843Retire  125 }

ne843RetireDc1Pmf   NOTIFICATION-TYPE
OBJECTS     { ne843TrapDesc, ne843TrapSev, ne843TrapTime, ne843TrapDate, ne843TrapPath }
STATUS      current
DESCRIPTION
        "Probe Minimum Fail"
 ::= { ne843Retire  126 }

ne843RetirePs1Crt   NOTIFICATION-TYPE
OBJECTS     { ne843TrapDesc, ne843TrapSev, ne843TrapTime, ne843TrapDate, ne843TrapPath }
STATUS      current
DESCRIPTION
        "Configuration Changed Reboot Required"
 ::= { ne843Retire  127 }

ne843RetireIvp1Milv   NOTIFICATION-TYPE
OBJECTS     { ne843TrapDesc, ne843TrapSev, ne843TrapTime, ne843TrapDate, ne843TrapPath }
STATUS      current
DESCRIPTION
        "Multiple Inverter Low Input Voltage"
 ::= { ne843Retire  128 }

ne843RetireDc1Faja   NOTIFICATION-TYPE
OBJECTS     { ne843TrapDesc, ne843TrapSev, ne843TrapTime, ne843TrapDate, ne843TrapPath }
STATUS      current
DESCRIPTION
        "Distribution Fuse A"
 ::= { ne843Retire  129 }

ne843RetireDc1Buht   NOTIFICATION-TYPE
OBJECTS     { ne843TrapDesc, ne843TrapSev, ne843TrapTime, ne843TrapDate, ne843TrapPath }
STATUS      current
DESCRIPTION
        "Bus Hi Temp"
 ::= { ne843Retire  130 }

ne843RetireDc1Buvht   NOTIFICATION-TYPE
OBJECTS     { ne843TrapDesc, ne843TrapSev, ne843TrapTime, ne843TrapDate, ne843TrapPath }
STATUS      current
DESCRIPTION
        "Bus Very Hi Temp"
 ::= { ne843Retire  131 }

ne843RetireDc1Btha   NOTIFICATION-TYPE
OBJECTS     { ne843TrapDesc, ne843TrapSev, ne843TrapTime, ne843TrapDate, ne843TrapPath }
STATUS      current
DESCRIPTION
        "Batt Hi Temp"
 ::= { ne843Retire  132 }

ne843RetireDc1Btvh   NOTIFICATION-TYPE
OBJECTS     { ne843TrapDesc, ne843TrapSev, ne843TrapTime, ne843TrapDate, ne843TrapPath }
STATUS      current
DESCRIPTION
        "Batt Very Hi Temp"
 ::= { ne843Retire  133 }

ne843RetireDc1Btla   NOTIFICATION-TYPE
OBJECTS     { ne843TrapDesc, ne843TrapSev, ne843TrapTime, ne843TrapDate, ne843TrapPath }
STATUS      current
DESCRIPTION
        "Batt Low Temp"
 ::= { ne843Retire  134 }

ne843RetireDc1Btvl   NOTIFICATION-TYPE
OBJECTS     { ne843TrapDesc, ne843TrapSev, ne843TrapTime, ne843TrapDate, ne843TrapPath }
STATUS      current
DESCRIPTION
        "Batt Very Low Temp"
 ::= { ne843Retire  135 }

ne843RetireDc1Laht   NOTIFICATION-TYPE
OBJECTS     { ne843TrapDesc, ne843TrapSev, ne843TrapTime, ne843TrapDate, ne843TrapPath }
STATUS      current
DESCRIPTION
        "Local Amb. Hi Temp"
 ::= { ne843Retire  136 }

ne843RetireDc1Lalt   NOTIFICATION-TYPE
OBJECTS     { ne843TrapDesc, ne843TrapSev, ne843TrapTime, ne843TrapDate, ne843TrapPath }
STATUS      current
DESCRIPTION
        "Local Amb. Low Temp"
 ::= { ne843Retire  137 }

ne843RetireDc1Raht   NOTIFICATION-TYPE
OBJECTS     { ne843TrapDesc, ne843TrapSev, ne843TrapTime, ne843TrapDate, ne843TrapPath }
STATUS      current
DESCRIPTION
        "Remote Amb. Hi Temp"
 ::= { ne843Retire  138 }

ne843RetireDc1Ravht   NOTIFICATION-TYPE
OBJECTS     { ne843TrapDesc, ne843TrapSev, ne843TrapTime, ne843TrapDate, ne843TrapPath }
STATUS      current
DESCRIPTION
        "Remote Amb. Very Hi Temp"
 ::= { ne843Retire  139 }

ne843RetireDc1Ralt   NOTIFICATION-TYPE
OBJECTS     { ne843TrapDesc, ne843TrapSev, ne843TrapTime, ne843TrapDate, ne843TrapPath }
STATUS      current
DESCRIPTION
        "Remote Amb. Low Temp"
 ::= { ne843Retire  140 }

ne843RetireDc1Vlva   NOTIFICATION-TYPE
OBJECTS     { ne843TrapDesc, ne843TrapSev, ne843TrapTime, ne843TrapDate, ne843TrapPath }
STATUS      current
DESCRIPTION
        "VA Power Loss"
 ::= { ne843Retire  141 }

ne843RetireDc1Vlvb   NOTIFICATION-TYPE
OBJECTS     { ne843TrapDesc, ne843TrapSev, ne843TrapTime, ne843TrapDate, ne843TrapPath }
STATUS      current
DESCRIPTION
        "VB Power Loss"
 ::= { ne843Retire  142 }

ne843RetireDc1Ovla   NOTIFICATION-TYPE
OBJECTS     { ne843TrapDesc, ne843TrapSev, ne843TrapTime, ne843TrapDate, ne843TrapPath }
STATUS      current
DESCRIPTION
        "IA Overload"
 ::= { ne843Retire  143 }

ne843RetireDc1Ovlb   NOTIFICATION-TYPE
OBJECTS     { ne843TrapDesc, ne843TrapSev, ne843TrapTime, ne843TrapDate, ne843TrapPath }
STATUS      current
DESCRIPTION
        "IB Overload"
 ::= { ne843Retire  144 }

ne843RetireDc1Pcaux   NOTIFICATION-TYPE
OBJECTS     { ne843TrapDesc, ne843TrapSev, ne843TrapTime, ne843TrapDate, ne843TrapPath }
STATUS      current
DESCRIPTION
        "PIC Auxiliary"
 ::= { ne843Retire  145 }

ne843RetireDc1Slot   NOTIFICATION-TYPE
OBJECTS     { ne843TrapDesc, ne843TrapSev, ne843TrapTime, ne843TrapDate, ne843TrapPath }
STATUS      current
DESCRIPTION
        "PIC Slot"
 ::= { ne843Retire  146 }

ne843RetireDc1Fajb   NOTIFICATION-TYPE
OBJECTS     { ne843TrapDesc, ne843TrapSev, ne843TrapTime, ne843TrapDate, ne843TrapPath }
STATUS      current
DESCRIPTION
        "Distribution Fuse B"
 ::= { ne843Retire  147 }

ne843RetireDc1Smw   NOTIFICATION-TYPE
OBJECTS     { ne843TrapDesc, ne843TrapSev, ne843TrapTime, ne843TrapDate, ne843TrapPath }
STATUS      current
DESCRIPTION
        "Shunt Mis-wired"
 ::= { ne843Retire  148 }

ne843RetireDc1Cca   NOTIFICATION-TYPE
OBJECTS     { ne843TrapDesc, ne843TrapSev, ne843TrapTime, ne843TrapDate, ne843TrapPath }
STATUS      current
DESCRIPTION
        "Circuit Assignment"
 ::= { ne843Retire  149 }

--
-- object ne843Acd1
--

ne843Acd1 OBJECT IDENTIFIER  ::= { ne843  38 }

ne843Acd1Ide OBJECT-TYPE
SYNTAX      DisplayString
MAX-ACCESS  read-only
STATUS      current
DESCRIPTION
"Identifier"
 ::= { ne843Acd1  1 }

ne843Acd1Des OBJECT-TYPE
SYNTAX      DisplayString
MAX-ACCESS  read-write
STATUS      current
DESCRIPTION
"Description"
 ::= { ne843Acd1  2 }

ne843Acd1Brc OBJECT-TYPE
SYNTAX      DisplayString
MAX-ACCESS  read-only
STATUS      current
DESCRIPTION
"Board Code"
 ::= { ne843Acd1  3 }

ne843Acd1Sn OBJECT-TYPE
SYNTAX      DisplayString
MAX-ACCESS  read-only
STATUS      current
DESCRIPTION
"Serial Number"
 ::= { ne843Acd1  4 }

ne843Acd1Prd OBJECT-TYPE
SYNTAX      DisplayString
MAX-ACCESS  read-write
STATUS      current
DESCRIPTION
"Phase 1 Description"
 ::= { ne843Acd1  5 }

ne843Acd1Psd OBJECT-TYPE
SYNTAX      DisplayString
MAX-ACCESS  read-write
STATUS      current
DESCRIPTION
"Phase 2 Description"
 ::= { ne843Acd1  6 }

ne843Acd1Ptd OBJECT-TYPE
SYNTAX      DisplayString
MAX-ACCESS  read-write
STATUS      current
DESCRIPTION
"Phase 3 Description"
 ::= { ne843Acd1  7 }

ne843Acd1Prv OBJECT-TYPE
SYNTAX      DisplayString
UNITS       "Vrms"
MAX-ACCESS  read-only
STATUS      current
DESCRIPTION
"Phase 1 Voltage (Vrms)"
 ::= { ne843Acd1  8 }

ne843Acd1Psv OBJECT-TYPE
SYNTAX      DisplayString
UNITS       "Vrms"
MAX-ACCESS  read-only
STATUS      current
DESCRIPTION
"Phase 2 Voltage (Vrms)"
 ::= { ne843Acd1  9 }

ne843Acd1Ptv OBJECT-TYPE
SYNTAX      DisplayString
UNITS       "Vrms"
MAX-ACCESS  read-only
STATUS      current
DESCRIPTION
"Phase 3 Voltage (Vrms)"
 ::= { ne843Acd1  10 }

ne843Acd1Pra OBJECT-TYPE
SYNTAX      DisplayString
UNITS       "Amps"
MAX-ACCESS  read-only
STATUS      current
DESCRIPTION
"Phase 1 Current (Amps)"
 ::= { ne843Acd1  11 }

ne843Acd1Psa OBJECT-TYPE
SYNTAX      DisplayString
UNITS       "Amps"
MAX-ACCESS  read-only
STATUS      current
DESCRIPTION
"Phase 2 Current (Amps)"
 ::= { ne843Acd1  12 }

ne843Acd1Pta OBJECT-TYPE
SYNTAX      DisplayString
UNITS       "Amps"
MAX-ACCESS  read-only
STATUS      current
DESCRIPTION
"Phase 3 Current (Amps)"
 ::= { ne843Acd1  13 }

ne843Acd1Prf OBJECT-TYPE
SYNTAX      DisplayString
UNITS       "Hz"
MAX-ACCESS  read-only
STATUS      current
DESCRIPTION
"Phase 1 Frequency (Hz)"
 ::= { ne843Acd1  14 }

ne843Acd1Psf OBJECT-TYPE
SYNTAX      DisplayString
UNITS       "Hz"
MAX-ACCESS  read-only
STATUS      current
DESCRIPTION
"Phase 2 Frequency (Hz)"
 ::= { ne843Acd1  15 }

ne843Acd1Ptf OBJECT-TYPE
SYNTAX      DisplayString
UNITS       "Hz"
MAX-ACCESS  read-only
STATUS      current
DESCRIPTION
"Phase 3 Frequency (Hz)"
 ::= { ne843Acd1  16 }

ne843Acd1Prk OBJECT-TYPE
SYNTAX      DisplayString
UNITS       "kW"
MAX-ACCESS  read-only
STATUS      current
DESCRIPTION
"Phase 1 Power (kW)"
 ::= { ne843Acd1  17 }

ne843Acd1Psk OBJECT-TYPE
SYNTAX      DisplayString
UNITS       "kW"
MAX-ACCESS  read-only
STATUS      current
DESCRIPTION
"Phase 2 Power (kW)"
 ::= { ne843Acd1  18 }

ne843Acd1Ptk OBJECT-TYPE
SYNTAX      DisplayString
UNITS       "kW"
MAX-ACCESS  read-only
STATUS      current
DESCRIPTION
"Phase 3 Power (kW)"
 ::= { ne843Acd1  19 }

ne843Acd1Syk OBJECT-TYPE
SYNTAX      DisplayString
UNITS       "kW"
MAX-ACCESS  read-only
STATUS      current
DESCRIPTION
"Total Power (kW)"
 ::= { ne843Acd1  20 }

ne843Acd1Prx OBJECT-TYPE
SYNTAX      DisplayString
MAX-ACCESS  read-write
STATUS      current
DESCRIPTION
"Phase 1 CTR"
 ::= { ne843Acd1  21 }

ne843Acd1Psx OBJECT-TYPE
SYNTAX      DisplayString
MAX-ACCESS  read-write
STATUS      current
DESCRIPTION
"Phase 2 CTR"
 ::= { ne843Acd1  22 }

ne843Acd1Ptx OBJECT-TYPE
SYNTAX      DisplayString
MAX-ACCESS  read-write
STATUS      current
DESCRIPTION
"Phase 3 CTR"
 ::= { ne843Acd1  23 }


--
-- object ne843Gn1
--

ne843Gn1 OBJECT IDENTIFIER  ::= { ne843  39 }

ne843Gn1Ide OBJECT-TYPE
SYNTAX      DisplayString
MAX-ACCESS  read-only
STATUS      current
DESCRIPTION
"Identifier"
 ::= { ne843Gn1  1 }

ne843Gn1Des OBJECT-TYPE
SYNTAX      DisplayString
MAX-ACCESS  read-write
STATUS      current
DESCRIPTION
"Description"
 ::= { ne843Gn1  2 }

ne843Gn1Rt OBJECT-TYPE
SYNTAX      DisplayString
MAX-ACCESS  read-write
STATUS      current
DESCRIPTION
"Cumulative Runtime"
 ::= { ne843Gn1  3 }

ne843Gn1Trt OBJECT-TYPE
SYNTAX      DisplayString
MAX-ACCESS  read-only
STATUS      current
DESCRIPTION
"Current Runtime"
 ::= { ne843Gn1  4 }

ne843Gn1Gnr OBJECT-TYPE
SYNTAX      DisplayString
MAX-ACCESS  read-only
STATUS      current
DESCRIPTION
"Generator Running
Value:
Alarm report from GNR1
"
 ::= { ne843Gn1  5 }

ne843Gn1Gnm OBJECT-TYPE
SYNTAX      DisplayString
MAX-ACCESS  read-only
STATUS      current
DESCRIPTION
"Generator Maintenance Required
Value:
Alarm report from GNM1
"
 ::= { ne843Gn1  6 }

ne843Gn1Gnf OBJECT-TYPE
SYNTAX      DisplayString
MAX-ACCESS  read-only
STATUS      current
DESCRIPTION
"Generator Fail
Value:
Alarm report from GNF1
"
 ::= { ne843Gn1  7 }

ne843Gn1Clt OBJECT-TYPE
SYNTAX      Integer32(5..1000)
UNITS       "Amps"
MAX-ACCESS  read-write
STATUS      current
DESCRIPTION
"Current Limit Threshold (Amps)"
 ::= { ne843Gn1  8 }

ne843Gn1Tv OBJECT-TYPE
SYNTAX      Integer32(19..28|40..56)
MAX-ACCESS  read-write
STATUS      current
DESCRIPTION
"Start Voltage"
 ::= { ne843Gn1  9 }

ne843Gn1Tvd OBJECT-TYPE
SYNTAX      DisplayString
MAX-ACCESS  read-write
STATUS      current
DESCRIPTION
"Start Voltage Delay"
 ::= { ne843Gn1  10 }

ne843Gn1Tp OBJECT-TYPE
SYNTAX      Integer32(10..100)
MAX-ACCESS  read-write
STATUS      current
DESCRIPTION
"Start Percent of Charge"
 ::= { ne843Gn1  11 }

ne843Gn1Tpd OBJECT-TYPE
SYNTAX      DisplayString
MAX-ACCESS  read-write
STATUS      current
DESCRIPTION
"Start POC Delay"
 ::= { ne843Gn1  12 }

ne843Gn1Tct OBJECT-TYPE
SYNTAX      Integer32
UNITS       "ambient"
MAX-ACCESS  read-write
STATUS      current
DESCRIPTION
"Start Cooling (ambient) Temperature (C)"
 ::= { ne843Gn1  13 }

ne843Gn1Tctd OBJECT-TYPE
SYNTAX      DisplayString
MAX-ACCESS  read-write
STATUS      current
DESCRIPTION
"Start Cooling Temperature Delay"
 ::= { ne843Gn1  14 }

ne843Gn1Tht OBJECT-TYPE
SYNTAX      Integer32
UNITS       "ambient"
MAX-ACCESS  read-write
STATUS      current
DESCRIPTION
"Start Heating (ambient) Temperature (C)"
 ::= { ne843Gn1  15 }

ne843Gn1Thtd OBJECT-TYPE
SYNTAX      DisplayString
MAX-ACCESS  read-write
STATUS      current
DESCRIPTION
"Start Heating Temperature Delay"
 ::= { ne843Gn1  16 }

ne843Gn1Pv OBJECT-TYPE
SYNTAX      Integer32(21..30|46..60)
MAX-ACCESS  read-write
STATUS      current
DESCRIPTION
"Stop Voltage"
 ::= { ne843Gn1  17 }

ne843Gn1Pvd OBJECT-TYPE
SYNTAX      DisplayString
MAX-ACCESS  read-write
STATUS      current
DESCRIPTION
"Stop Voltage Delay"
 ::= { ne843Gn1  18 }

ne843Gn1Pi OBJECT-TYPE
SYNTAX      Integer32(2..50)
MAX-ACCESS  read-write
STATUS      current
DESCRIPTION
"Stop Current"
 ::= { ne843Gn1  19 }

ne843Gn1Pid OBJECT-TYPE
SYNTAX      DisplayString
MAX-ACCESS  read-write
STATUS      current
DESCRIPTION
"Stop Current Delay"
 ::= { ne843Gn1  20 }

ne843Gn1Pp OBJECT-TYPE
SYNTAX      Integer32(10..100)
MAX-ACCESS  read-write
STATUS      current
DESCRIPTION
"Stop Percent of Charge"
 ::= { ne843Gn1  21 }

ne843Gn1Ppd OBJECT-TYPE
SYNTAX      DisplayString
MAX-ACCESS  read-write
STATUS      current
DESCRIPTION
"Stop POC Delay"
 ::= { ne843Gn1  22 }

ne843Gn1Pct OBJECT-TYPE
SYNTAX      Integer32
UNITS       "ambient"
MAX-ACCESS  read-write
STATUS      current
DESCRIPTION
"Stop Cooling (ambient) Temperature (C)"
 ::= { ne843Gn1  23 }

ne843Gn1Pctd OBJECT-TYPE
SYNTAX      DisplayString
MAX-ACCESS  read-write
STATUS      current
DESCRIPTION
"Stop Cooling Temperature Delay"
 ::= { ne843Gn1  24 }

ne843Gn1Pht OBJECT-TYPE
SYNTAX      Integer32
UNITS       "ambient"
MAX-ACCESS  read-write
STATUS      current
DESCRIPTION
"Stop Heating (ambient) Temperature (C)"
 ::= { ne843Gn1  25 }

ne843Gn1Phtd OBJECT-TYPE
SYNTAX      DisplayString
MAX-ACCESS  read-write
STATUS      current
DESCRIPTION
"Stop Heating Temperature Delay"
 ::= { ne843Gn1  26 }

ne843Gn1Mrt OBJECT-TYPE
SYNTAX      DisplayString
MAX-ACCESS  read-write
STATUS      current
DESCRIPTION
"Mininum Run Time"
 ::= { ne843Gn1  27 }

ne843Gn1Tve OBJECT-TYPE
SYNTAX      INTEGER {
disable(0),
enable(1)
}
MAX-ACCESS  read-write
STATUS      current
DESCRIPTION
"Start Voltage Enable
Values:
disable(0),
enable(1)
"
 ::= { ne843Gn1  28 }

ne843Gn1Tpe OBJECT-TYPE
SYNTAX      INTEGER {
disable(0),
enable(1)
}
MAX-ACCESS  read-write
STATUS      current
DESCRIPTION
"Start Percent of Charge Enable
Values:
disable(0),
enable(1)
"
 ::= { ne843Gn1  29 }

ne843Gn1Cte OBJECT-TYPE
SYNTAX      INTEGER {
disable(0),
enable(1)
}
MAX-ACCESS  read-write
STATUS      current
DESCRIPTION
"Start Cooling Temperatuer Enable
Values:
disable(0),
enable(1)
"
 ::= { ne843Gn1  30 }

ne843Gn1Hte OBJECT-TYPE
SYNTAX      INTEGER {
disable(0),
enable(1)
}
MAX-ACCESS  read-write
STATUS      current
DESCRIPTION
"Start Heating Temperatuer Enable
Values:
disable(0),
enable(1)
"
 ::= { ne843Gn1  31 }

ne843Gn1Pve OBJECT-TYPE
SYNTAX      INTEGER {
disable(0),
enable(1)
}
MAX-ACCESS  read-write
STATUS      current
DESCRIPTION
"Stop Voltage Enable
Values:
disable(0),
enable(1)
"
 ::= { ne843Gn1  32 }

ne843Gn1Pie OBJECT-TYPE
SYNTAX      INTEGER {
disable(0),
enable(1)
}
MAX-ACCESS  read-write
STATUS      current
DESCRIPTION
"Stop Current Enable
Values:
disable(0),
enable(1)
"
 ::= { ne843Gn1  33 }

ne843Gn1Ppe OBJECT-TYPE
SYNTAX      INTEGER {
disable(0),
enable(1)
}
MAX-ACCESS  read-write
STATUS      current
DESCRIPTION
"Stop Percent of Charge Enable
Values:
disable(0),
enable(1)
"
 ::= { ne843Gn1  34 }

ne843Gn1Nv OBJECT-TYPE
SYNTAX      Integer32(0..999)
MAX-ACCESS  read-write
STATUS      current
DESCRIPTION
"Nominal Output Voltage"
 ::= { ne843Gn1  35 }

ne843Gn1Nva OBJECT-TYPE
SYNTAX      Integer32(0..999000)
MAX-ACCESS  read-write
STATUS      current
DESCRIPTION
"Nominal Output Power"
 ::= { ne843Gn1  36 }

ne843Gn1Ode OBJECT-TYPE
SYNTAX      INTEGER {
disable(0),
enable(1)
}
MAX-ACCESS  read-write
STATUS      current
DESCRIPTION
"Manual on Duration Enable
Values:
disable(0),
enable(1)
"
 ::= { ne843Gn1  37 }

ne843Gn1Odr OBJECT-TYPE
SYNTAX      DisplayString
MAX-ACCESS  read-write
STATUS      current
DESCRIPTION
"Manual on Duration"
 ::= { ne843Gn1  38 }

ne843Gn1Ocd OBJECT-TYPE
SYNTAX      DisplayString
MAX-ACCESS  read-only
STATUS      current
DESCRIPTION
"Manual on Duration countdown"
 ::= { ne843Gn1  39 }

ne843Gn1Gns OBJECT-TYPE
SYNTAX      DisplayString
MAX-ACCESS  read-only
STATUS      current
DESCRIPTION
"Generator Start
Value:
Alarm report from GNS1
"
 ::= { ne843Gn1  40 }

ne843Gn1Aue OBJECT-TYPE
SYNTAX      INTEGER {
disable(0),
enable(1)
}
MAX-ACCESS  read-write
STATUS      current
DESCRIPTION
"Auto Mode Enable
Values:
disable(0),
enable(1)
"
 ::= { ne843Gn1  41 }

ne843Gn1Mod OBJECT-TYPE
SYNTAX      DisplayString
MAX-ACCESS  read-write
STATUS      current
DESCRIPTION
"Auto Mode
Values:
OFF,
ON,
AUTO
"
 ::= { ne843Gn1  42 }

ne843Gn1Stt OBJECT-TYPE
SYNTAX      DisplayString
MAX-ACCESS  read-only
STATUS      current
DESCRIPTION
"State"
 ::= { ne843Gn1  43 }


--
-- table BAT
--

ne843BatTable    OBJECT-TYPE
SYNTAX SEQUENCE OF Ne843BatEntry
MAX-ACCESS not-accessible
STATUS current
DESCRIPTION
        "Table of all Battery Section data"
 ::= { ne843  40 }

ne843BatEntry OBJECT-TYPE
SYNTAX     Ne843BatEntry
MAX-ACCESS  not-accessible
STATUS      current
DESCRIPTION
       "Entry of information for one Battery Section"
INDEX { ne843BatEntryIndex }
 ::= { ne843BatTable  1 }

Ne843BatEntry ::= SEQUENCE {
ne843BatEntryIndex   INTEGER,
ne843BatEntryIde   DisplayString,
ne843BatEntryDes   DisplayString,
ne843BatEntryCon   DisplayString,
ne843BatEntryStt   DisplayString,
ne843BatEntryNst   DisplayString,
ne843BatEntryBty   DisplayString,
ne843BatEntryCap   DisplayString,
ne843BatEntryDat   DisplayString,
ne843BatEntryMpv   DisplayString,
ne843BatEntryAdc   DisplayString
}

ne843BatEntryIndex OBJECT-TYPE
SYNTAX      INTEGER (0..2147483647)
MAX-ACCESS  read-only
STATUS      current
DESCRIPTION
"Table Index"
 ::= { ne843BatEntry  1 }

ne843BatEntryIde OBJECT-TYPE
SYNTAX      DisplayString
MAX-ACCESS  read-only
STATUS      current
DESCRIPTION
"Identifier"
 ::= { ne843BatEntry  2 }

ne843BatEntryDes OBJECT-TYPE
SYNTAX      DisplayString
MAX-ACCESS  read-write
STATUS      current
DESCRIPTION
"Description"
 ::= { ne843BatEntry  3 }

ne843BatEntryCon OBJECT-TYPE
SYNTAX      DisplayString
MAX-ACCESS  read-write
STATUS      current
DESCRIPTION
"Contactor"
 ::= { ne843BatEntry  4 }

ne843BatEntryStt OBJECT-TYPE
SYNTAX      DisplayString
MAX-ACCESS  read-only
STATUS      current
DESCRIPTION
"State"
 ::= { ne843BatEntry  5 }

ne843BatEntryNst OBJECT-TYPE
SYNTAX      DisplayString
MAX-ACCESS  read-write
STATUS      current
DESCRIPTION
"Number of Strings"
 ::= { ne843BatEntry  6 }

ne843BatEntryBty OBJECT-TYPE
SYNTAX      DisplayString
MAX-ACCESS  read-only
STATUS      current
DESCRIPTION
"Battery Type"
 ::= { ne843BatEntry  7 }

ne843BatEntryCap OBJECT-TYPE
SYNTAX      DisplayString
MAX-ACCESS  read-only
STATUS      current
DESCRIPTION
"Capacity"
 ::= { ne843BatEntry  8 }

ne843BatEntryDat OBJECT-TYPE
SYNTAX      DisplayString
MAX-ACCESS  read-only
STATUS      current
DESCRIPTION
"Install Date"
 ::= { ne843BatEntry  9 }

ne843BatEntryMpv OBJECT-TYPE
SYNTAX      DisplayString
UNITS       "Volts"
MAX-ACCESS  read-only
STATUS      current
DESCRIPTION
"Midtstring Voltage (Volts)"
 ::= { ne843BatEntry  10 }

ne843BatEntryAdc OBJECT-TYPE
SYNTAX      DisplayString
UNITS       "Amps"
MAX-ACCESS  read-only
STATUS      current
DESCRIPTION
"Current (Amps)"
 ::= { ne843BatEntry  11 }



--
-- object ne843Eco1
--

ne843Eco1 OBJECT IDENTIFIER  ::= { ne843  41 }

ne843Eco1Ide OBJECT-TYPE
SYNTAX      DisplayString
MAX-ACCESS  read-only
STATUS      current
DESCRIPTION
"Identifier"
 ::= { ne843Eco1  1 }

ne843Eco1Des OBJECT-TYPE
SYNTAX      DisplayString
MAX-ACCESS  read-write
STATUS      current
DESCRIPTION
"Description"
 ::= { ne843Eco1  2 }

ne843Eco1Sofs OBJECT-TYPE
SYNTAX      DisplayString
MAX-ACCESS  read-write
STATUS      current
DESCRIPTION
"Solar Rectifier Offset"
 ::= { ne843Eco1  3 }

ne843Eco1Ntrd OBJECT-TYPE
SYNTAX      DisplayString
MAX-ACCESS  read-only
STATUS      current
DESCRIPTION
"Normal Rectifier Drain"
 ::= { ne843Eco1  4 }

ne843Eco1Strd OBJECT-TYPE
SYNTAX      DisplayString
MAX-ACCESS  read-only
STATUS      current
DESCRIPTION
"Solar Rectifier Drain"
 ::= { ne843Eco1  5 }

ne843Eco1Nkwh OBJECT-TYPE
SYNTAX      DisplayString
MAX-ACCESS  read-only
STATUS      current
DESCRIPTION
"Normal kWh"
 ::= { ne843Eco1  6 }

ne843Eco1Skwh OBJECT-TYPE
SYNTAX      DisplayString
MAX-ACCESS  read-only
STATUS      current
DESCRIPTION
"Solar kWh"
 ::= { ne843Eco1  7 }

ne843Eco1Ncap OBJECT-TYPE
SYNTAX      DisplayString
MAX-ACCESS  read-only
STATUS      current
DESCRIPTION
"Normal Capacity"
 ::= { ne843Eco1  8 }

ne843Eco1Nocap OBJECT-TYPE
SYNTAX      DisplayString
MAX-ACCESS  read-only
STATUS      current
DESCRIPTION
"Normal Online Capacity"
 ::= { ne843Eco1  9 }


--
-- object ne843Ivp1
--

ne843Ivp1 OBJECT IDENTIFIER  ::= { ne843  42 }

ne843Ivp1Ide OBJECT-TYPE
SYNTAX      DisplayString
MAX-ACCESS  read-only
STATUS      current
DESCRIPTION
"Identifier"
 ::= { ne843Ivp1  1 }

ne843Ivp1Des OBJECT-TYPE
SYNTAX      DisplayString
MAX-ACCESS  read-write
STATUS      current
DESCRIPTION
"Description"
 ::= { ne843Ivp1  2 }

ne843Ivp1Cap OBJECT-TYPE
SYNTAX      Integer32
UNITS       "Amps"
MAX-ACCESS  read-only
STATUS      current
DESCRIPTION
"Total Installed Inverter Capacity (Amps)"
 ::= { ne843Ivp1  3 }

ne843Ivp1Irm OBJECT-TYPE
SYNTAX      Integer32
MAX-ACCESS  read-only
STATUS      current
DESCRIPTION
"RMS Current"
 ::= { ne843Ivp1  4 }

ne843Ivp1Vac OBJECT-TYPE
SYNTAX      Integer32
MAX-ACCESS  read-only
STATUS      current
DESCRIPTION
"AC Output voltage"
 ::= { ne843Ivp1  5 }

ne843Ivp1Adc OBJECT-TYPE
SYNTAX      Integer32
MAX-ACCESS  read-only
STATUS      current
DESCRIPTION
"DC Current"
 ::= { ne843Ivp1  6 }

ne843Ivp1Vdc OBJECT-TYPE
SYNTAX      Integer32
MAX-ACCESS  read-only
STATUS      current
DESCRIPTION
"DC Voltage"
 ::= { ne843Ivp1  7 }

ne843Ivp1Frq OBJECT-TYPE
SYNTAX      Integer32
MAX-ACCESS  read-only
STATUS      current
DESCRIPTION
"Frequency"
 ::= { ne843Ivp1  8 }

ne843Ivp1Lst OBJECT-TYPE
SYNTAX      Integer32
MAX-ACCESS  read-only
STATUS      current
DESCRIPTION
"Load Share Target Percentage"
 ::= { ne843Ivp1  9 }

ne843Ivp1Ste OBJECT-TYPE
SYNTAX      INTEGER {
disable(0),
enable(1)
}
MAX-ACCESS  read-write
STATUS      current
DESCRIPTION
"Standby Enabled
Values:
disable(0),
enable(1)
"
 ::= { ne843Ivp1  10 }

ne843Ivp1Rlse OBJECT-TYPE
SYNTAX      INTEGER {
disable(0),
enable(1)
}
MAX-ACCESS  read-write
STATUS      current
DESCRIPTION
"Redundancy Loss Enabled
Values:
disable(0),
enable(1)
"
 ::= { ne843Ivp1  11 }

ne843Ivp1Dth OBJECT-TYPE
SYNTAX      Integer32(20..25|40..50)
MAX-ACCESS  read-write
STATUS      current
DESCRIPTION
"Low Voltage Disconnect Threshold"
 ::= { ne843Ivp1  12 }

ne843Ivp1Rth OBJECT-TYPE
SYNTAX      Integer32(22..27|44..54)
MAX-ACCESS  read-write
STATUS      current
DESCRIPTION
"Low Voltage Reconnect Threshold"
 ::= { ne843Ivp1  13 }

ne843Ivp1Lvd OBJECT-TYPE
SYNTAX      INTEGER {
disable(0),
enable(1)
}
MAX-ACCESS  read-write
STATUS      current
DESCRIPTION
"Low Voltage Disconnect Enabled
Values:
disable(0),
enable(1)
"
 ::= { ne843Ivp1  14 }

ne843Ivp1Hce OBJECT-TYPE
SYNTAX      INTEGER {
disable(0),
enable(1)
}
MAX-ACCESS  read-write
STATUS      current
DESCRIPTION
"Hi Crest Factor Enabled
Values:
disable(0),
enable(1)
"
 ::= { ne843Ivp1  15 }

ne843Ivp1Hipe OBJECT-TYPE
SYNTAX      INTEGER {
disable(0),
enable(1)
}
MAX-ACCESS  read-write
STATUS      current
DESCRIPTION
"Hi IPeak Current Enabled
Values:
disable(0),
enable(1)
"
 ::= { ne843Ivp1  16 }

ne843Ivp1Hrme OBJECT-TYPE
SYNTAX      INTEGER {
disable(0),
enable(1)
}
MAX-ACCESS  read-write
STATUS      current
DESCRIPTION
"Hi IRMS Currrent Enabled
Values:
disable(0),
enable(1)
"
 ::= { ne843Ivp1  17 }

ne843Ivp1Ilvi OBJECT-TYPE
SYNTAX      DisplayString
MAX-ACCESS  read-only
STATUS      current
DESCRIPTION
"Inverter Low Input
Value:
Alarm report from ILVI1
"
 ::= { ne843Ivp1  18 }

ne843Ivp1Ihvi OBJECT-TYPE
SYNTAX      DisplayString
MAX-ACCESS  read-only
STATUS      current
DESCRIPTION
"Inverter High Input
Value:
Alarm report from IHVI1
"
 ::= { ne843Ivp1  19 }

ne843Ivp1Ita OBJECT-TYPE
SYNTAX      DisplayString
MAX-ACCESS  read-only
STATUS      current
DESCRIPTION
"Inverter High Temperature
Value:
Alarm report from ITA1
"
 ::= { ne843Ivp1  20 }

ne843Ivp1If OBJECT-TYPE
SYNTAX      DisplayString
MAX-ACCESS  read-only
STATUS      current
DESCRIPTION
"Inverter Fail
Value:
Alarm report from IF1
"
 ::= { ne843Ivp1  21 }

ne843Ivp1Ilv OBJECT-TYPE
SYNTAX      DisplayString
MAX-ACCESS  read-only
STATUS      current
DESCRIPTION
"Inverter Low Output
Value:
Alarm report from ILV1
"
 ::= { ne843Ivp1  22 }

ne843Ivp1Ifa OBJECT-TYPE
SYNTAX      DisplayString
MAX-ACCESS  read-only
STATUS      current
DESCRIPTION
"Inverter Frequency Lock
Value:
Alarm report from IFA1
"
 ::= { ne843Ivp1  23 }

ne843Ivp1Ihv OBJECT-TYPE
SYNTAX      DisplayString
MAX-ACCESS  read-only
STATUS      current
DESCRIPTION
"Inverter High Output
Value:
Alarm report from IHV1
"
 ::= { ne843Ivp1  24 }

ne843Ivp1Ida OBJECT-TYPE
SYNTAX      DisplayString
MAX-ACCESS  read-only
STATUS      current
DESCRIPTION
"Inverter Distribution Alarm
Value:
Alarm report from IDA1
"
 ::= { ne843Ivp1  25 }

ne843Ivp1Iof OBJECT-TYPE
SYNTAX      DisplayString
MAX-ACCESS  read-only
STATUS      current
DESCRIPTION
"Inverter Output Fuse
Value:
Alarm report from IOF1
"
 ::= { ne843Ivp1  26 }

ne843Ivp1Idid OBJECT-TYPE
SYNTAX      DisplayString
MAX-ACCESS  read-only
STATUS      current
DESCRIPTION
"Inverter ID Conflict
Value:
Alarm report from IDID1
"
 ::= { ne843Ivp1  27 }

ne843Ivp1Iirm OBJECT-TYPE
SYNTAX      DisplayString
MAX-ACCESS  read-only
STATUS      current
DESCRIPTION
"Inverter High RMS Current
Value:
Alarm report from IIRM1
"
 ::= { ne843Ivp1  28 }

ne843Ivp1Iipk OBJECT-TYPE
SYNTAX      DisplayString
MAX-ACCESS  read-only
STATUS      current
DESCRIPTION
"Inverter High Peak Current
Value:
Alarm report from IIPK1
"
 ::= { ne843Ivp1  29 }

ne843Ivp1Icf OBJECT-TYPE
SYNTAX      DisplayString
MAX-ACCESS  read-only
STATUS      current
DESCRIPTION
"Inverter High Crest Factor
Value:
Alarm report from ICF1
"
 ::= { ne843Ivp1  30 }

ne843Ivp1Mif OBJECT-TYPE
SYNTAX      DisplayString
MAX-ACCESS  read-only
STATUS      current
DESCRIPTION
"Multiple Inverter Fail
Value:
Alarm report from MIF1
"
 ::= { ne843Ivp1  31 }

ne843Ivp1Irls OBJECT-TYPE
SYNTAX      DisplayString
MAX-ACCESS  read-only
STATUS      current
DESCRIPTION
"Inverter Redundancy Loss
Value:
Alarm report from IRLS1
"
 ::= { ne843Ivp1  32 }

ne843Ivp1Milv OBJECT-TYPE
SYNTAX      DisplayString
MAX-ACCESS  read-only
STATUS      current
DESCRIPTION
"Multiple Inverter Low Input Voltage
Value:
Alarm report from MILV1
"
 ::= { ne843Ivp1  33 }


--
-- table INV
--

ne843InvTable    OBJECT-TYPE
SYNTAX SEQUENCE OF Ne843InvEntry
MAX-ACCESS not-accessible
STATUS current
DESCRIPTION
        "Table of all Inverter data"
 ::= { ne843  43 }

ne843InvEntry OBJECT-TYPE
SYNTAX     Ne843InvEntry
MAX-ACCESS  not-accessible
STATUS      current
DESCRIPTION
       "Entry of information for one Inverter"
INDEX { ne843InvEntryIndex }
 ::= { ne843InvTable  1 }

Ne843InvEntry ::= SEQUENCE {
ne843InvEntryIndex   INTEGER,
ne843InvEntryIde   DisplayString,
ne843InvEntryDes   DisplayString,
ne843InvEntryTyp   DisplayString,
ne843InvEntrySn   DisplayString,
ne843InvEntryAdc   Integer32,
ne843InvEntryVdc   Integer32,
ne843InvEntryVac   Integer32,
ne843InvEntryStt   DisplayString,
ne843InvEntryCap   Integer32,
ne843InvEntryCva   Integer32,
ne843InvEntryIpk   Integer32,
ne843InvEntryIrm   Integer32,
ne843InvEntryFrq   Integer32,
ne843InvEntryCf   Integer32,
ne843InvEntryPwr   Integer32,
ne843InvEntryVnom   Integer32,
ne843InvEntryNcl   INTEGER,
ne843InvEntryIlvi   DisplayString,
ne843InvEntryIta   DisplayString,
ne843InvEntryIf   DisplayString,
ne843InvEntryIlv   DisplayString,
ne843InvEntryIfa   DisplayString,
ne843InvEntryDid   DisplayString,
ne843InvEntryIcmf   DisplayString,
ne843InvEntryIcf   DisplayString,
ne843InvEntryIda   DisplayString,
ne843InvEntryIhv   DisplayString,
ne843InvEntryIhvi   DisplayString,
ne843InvEntryIipk   DisplayString,
ne843InvEntryIirm   DisplayString,
ne843InvEntryIof   DisplayString,
ne843InvEntryIlvi1   INTEGER,
ne843InvEntryIta1   INTEGER,
ne843InvEntryIf1   INTEGER,
ne843InvEntryIlv1   INTEGER,
ne843InvEntryIfa1   INTEGER,
ne843InvEntryDid1   INTEGER,
ne843InvEntryIcmf1   INTEGER,
ne843InvEntryIcf1   INTEGER,
ne843InvEntryIda1   INTEGER,
ne843InvEntryIhv1   INTEGER,
ne843InvEntryIhvi1   INTEGER,
ne843InvEntryIipk1   INTEGER,
ne843InvEntryIirm1   INTEGER,
ne843InvEntryIof1   INTEGER
}

ne843InvEntryIndex OBJECT-TYPE
SYNTAX      INTEGER (0..2147483647)
MAX-ACCESS  read-only
STATUS      current
DESCRIPTION
"Table Index"
 ::= { ne843InvEntry  1 }

ne843InvEntryIde OBJECT-TYPE
SYNTAX      DisplayString
MAX-ACCESS  read-only
STATUS      current
DESCRIPTION
"Identifier"
 ::= { ne843InvEntry  2 }

ne843InvEntryDes OBJECT-TYPE
SYNTAX      DisplayString
MAX-ACCESS  read-write
STATUS      current
DESCRIPTION
"Description"
 ::= { ne843InvEntry  3 }

ne843InvEntryTyp OBJECT-TYPE
SYNTAX      DisplayString
MAX-ACCESS  read-write
STATUS      current
DESCRIPTION
"Type"
 ::= { ne843InvEntry  4 }

ne843InvEntrySn OBJECT-TYPE
SYNTAX      DisplayString
MAX-ACCESS  read-only
STATUS      current
DESCRIPTION
"Serial Number"
 ::= { ne843InvEntry  5 }

ne843InvEntryAdc OBJECT-TYPE
SYNTAX      Integer32
UNITS       "Amps"
MAX-ACCESS  read-only
STATUS      current
DESCRIPTION
"DC Current (Amps)"
 ::= { ne843InvEntry  6 }

ne843InvEntryVdc OBJECT-TYPE
SYNTAX      Integer32
MAX-ACCESS  read-only
STATUS      current
DESCRIPTION
"DC Voltage"
 ::= { ne843InvEntry  7 }

ne843InvEntryVac OBJECT-TYPE
SYNTAX      Integer32
UNITS       "Volts"
MAX-ACCESS  read-only
STATUS      current
DESCRIPTION
"AC Voltage (Volts)"
 ::= { ne843InvEntry  8 }

ne843InvEntryStt OBJECT-TYPE
SYNTAX      DisplayString
MAX-ACCESS  read-write
STATUS      current
DESCRIPTION
"State
Values:
ON,
OFF,
STANDBY,
VACANT
"
 ::= { ne843InvEntry  9 }

ne843InvEntryCap OBJECT-TYPE
SYNTAX      Integer32
UNITS       "Amps"
MAX-ACCESS  read-only
STATUS      current
DESCRIPTION
"Capacity (Amps)"
 ::= { ne843InvEntry  10 }

ne843InvEntryCva OBJECT-TYPE
SYNTAX      Integer32
MAX-ACCESS  read-only
STATUS      current
DESCRIPTION
"Capacity in VA"
 ::= { ne843InvEntry  11 }

ne843InvEntryIpk OBJECT-TYPE
SYNTAX      Integer32
MAX-ACCESS  read-only
STATUS      current
DESCRIPTION
"Peak Current"
 ::= { ne843InvEntry  12 }

ne843InvEntryIrm OBJECT-TYPE
SYNTAX      Integer32
MAX-ACCESS  read-only
STATUS      current
DESCRIPTION
"RMS Current"
 ::= { ne843InvEntry  13 }

ne843InvEntryFrq OBJECT-TYPE
SYNTAX      Integer32
MAX-ACCESS  read-only
STATUS      current
DESCRIPTION
"Output Frequency"
 ::= { ne843InvEntry  14 }

ne843InvEntryCf OBJECT-TYPE
SYNTAX      Integer32
MAX-ACCESS  read-only
STATUS      current
DESCRIPTION
"Crest Factor"
 ::= { ne843InvEntry  15 }

ne843InvEntryPwr OBJECT-TYPE
SYNTAX      Integer32
MAX-ACCESS  read-only
STATUS      current
DESCRIPTION
"Output Power"
 ::= { ne843InvEntry  16 }

ne843InvEntryVnom OBJECT-TYPE
SYNTAX      Integer32
MAX-ACCESS  read-only
STATUS      current
DESCRIPTION
"Nominal Output Voltage"
 ::= { ne843InvEntry  17 }

ne843InvEntryNcl OBJECT-TYPE
SYNTAX      INTEGER {
disable(0),
enable(1)
}
UNITS       "for LVD"
MAX-ACCESS  read-write
STATUS      current
DESCRIPTION
"Non-Critical Load (for LVD)
Values:
disable(0),
enable(1)
"
 ::= { ne843InvEntry  18 }

ne843InvEntryIlvi OBJECT-TYPE
SYNTAX      DisplayString
MAX-ACCESS  read-only
STATUS      current
DESCRIPTION
"Low Voltage Input"
 ::= { ne843InvEntry  19 }

ne843InvEntryIta OBJECT-TYPE
SYNTAX      DisplayString
MAX-ACCESS  read-only
STATUS      current
DESCRIPTION
"Temperature Alarm"
 ::= { ne843InvEntry  20 }

ne843InvEntryIf OBJECT-TYPE
SYNTAX      DisplayString
MAX-ACCESS  read-only
STATUS      current
DESCRIPTION
"Inverter Fail"
 ::= { ne843InvEntry  21 }

ne843InvEntryIlv OBJECT-TYPE
SYNTAX      DisplayString
MAX-ACCESS  read-only
STATUS      current
DESCRIPTION
"Low Output Voltage"
 ::= { ne843InvEntry  22 }

ne843InvEntryIfa OBJECT-TYPE
SYNTAX      DisplayString
MAX-ACCESS  read-only
STATUS      current
DESCRIPTION
"Inverter Frequency Lock Fail"
 ::= { ne843InvEntry  23 }

ne843InvEntryDid OBJECT-TYPE
SYNTAX      DisplayString
MAX-ACCESS  read-only
STATUS      current
DESCRIPTION
"ID Conflict"
 ::= { ne843InvEntry  24 }

ne843InvEntryIcmf OBJECT-TYPE
SYNTAX      DisplayString
MAX-ACCESS  read-only
STATUS      current
DESCRIPTION
"Communication Failure"
 ::= { ne843InvEntry  25 }

ne843InvEntryIcf OBJECT-TYPE
SYNTAX      DisplayString
MAX-ACCESS  read-only
STATUS      current
DESCRIPTION
"Hi Crest Factor Status"
 ::= { ne843InvEntry  26 }

ne843InvEntryIda OBJECT-TYPE
SYNTAX      DisplayString
MAX-ACCESS  read-only
STATUS      current
DESCRIPTION
"Distribution Alarm Status"
 ::= { ne843InvEntry  27 }

ne843InvEntryIhv OBJECT-TYPE
SYNTAX      DisplayString
MAX-ACCESS  read-only
STATUS      current
DESCRIPTION
"High Output Status"
 ::= { ne843InvEntry  28 }

ne843InvEntryIhvi OBJECT-TYPE
SYNTAX      DisplayString
MAX-ACCESS  read-only
STATUS      current
DESCRIPTION
"High Input Status"
 ::= { ne843InvEntry  29 }

ne843InvEntryIipk OBJECT-TYPE
SYNTAX      DisplayString
MAX-ACCESS  read-only
STATUS      current
DESCRIPTION
"High IPeak Status"
 ::= { ne843InvEntry  30 }

ne843InvEntryIirm OBJECT-TYPE
SYNTAX      DisplayString
MAX-ACCESS  read-only
STATUS      current
DESCRIPTION
"High IRMS Status"
 ::= { ne843InvEntry  31 }

ne843InvEntryIof OBJECT-TYPE
SYNTAX      DisplayString
MAX-ACCESS  read-only
STATUS      current
DESCRIPTION
"Output Fuse Status"
 ::= { ne843InvEntry  32 }

ne843InvEntryIlvi1 OBJECT-TYPE
SYNTAX      INTEGER {
inactive(0),
active(1)
}
MAX-ACCESS  read-only
STATUS      current
DESCRIPTION
"Low Voltage Input
Values:
inactive(0),
active(1)
"
 ::= { ne843InvEntry  33 }

ne843InvEntryIta1 OBJECT-TYPE
SYNTAX      INTEGER {
inactive(0),
active(1)
}
MAX-ACCESS  read-only
STATUS      current
DESCRIPTION
"Temperature Alarm
Values:
inactive(0),
active(1)
"
 ::= { ne843InvEntry  34 }

ne843InvEntryIf1 OBJECT-TYPE
SYNTAX      INTEGER {
inactive(0),
active(1)
}
MAX-ACCESS  read-only
STATUS      current
DESCRIPTION
"Inverter Fail
Values:
inactive(0),
active(1)
"
 ::= { ne843InvEntry  35 }

ne843InvEntryIlv1 OBJECT-TYPE
SYNTAX      INTEGER {
inactive(0),
active(1)
}
MAX-ACCESS  read-only
STATUS      current
DESCRIPTION
"Low Output Voltage
Values:
inactive(0),
active(1)
"
 ::= { ne843InvEntry  36 }

ne843InvEntryIfa1 OBJECT-TYPE
SYNTAX      INTEGER {
inactive(0),
active(1)
}
MAX-ACCESS  read-only
STATUS      current
DESCRIPTION
"Inverter Frequency Lock Fail
Values:
inactive(0),
active(1)
"
 ::= { ne843InvEntry  37 }

ne843InvEntryDid1 OBJECT-TYPE
SYNTAX      INTEGER {
inactive(0),
active(1)
}
MAX-ACCESS  read-only
STATUS      current
DESCRIPTION
"ID Conflict
Values:
inactive(0),
active(1)
"
 ::= { ne843InvEntry  38 }

ne843InvEntryIcmf1 OBJECT-TYPE
SYNTAX      INTEGER {
inactive(0),
active(1)
}
MAX-ACCESS  read-only
STATUS      current
DESCRIPTION
"Communication Failure
Values:
inactive(0),
active(1)
"
 ::= { ne843InvEntry  39 }

ne843InvEntryIcf1 OBJECT-TYPE
SYNTAX      INTEGER {
inactive(0),
active(1)
}
MAX-ACCESS  read-only
STATUS      current
DESCRIPTION
"Hi Crest Factor Status
Values:
inactive(0),
active(1)
"
 ::= { ne843InvEntry  40 }

ne843InvEntryIda1 OBJECT-TYPE
SYNTAX      INTEGER {
inactive(0),
active(1)
}
MAX-ACCESS  read-only
STATUS      current
DESCRIPTION
"Distribution Alarm Status
Values:
inactive(0),
active(1)
"
 ::= { ne843InvEntry  41 }

ne843InvEntryIhv1 OBJECT-TYPE
SYNTAX      INTEGER {
inactive(0),
active(1)
}
MAX-ACCESS  read-only
STATUS      current
DESCRIPTION
"High Output Status
Values:
inactive(0),
active(1)
"
 ::= { ne843InvEntry  42 }

ne843InvEntryIhvi1 OBJECT-TYPE
SYNTAX      INTEGER {
inactive(0),
active(1)
}
MAX-ACCESS  read-only
STATUS      current
DESCRIPTION
"High Input Status
Values:
inactive(0),
active(1)
"
 ::= { ne843InvEntry  43 }

ne843InvEntryIipk1 OBJECT-TYPE
SYNTAX      INTEGER {
inactive(0),
active(1)
}
MAX-ACCESS  read-only
STATUS      current
DESCRIPTION
"High IPeak Status
Values:
inactive(0),
active(1)
"
 ::= { ne843InvEntry  44 }

ne843InvEntryIirm1 OBJECT-TYPE
SYNTAX      INTEGER {
inactive(0),
active(1)
}
MAX-ACCESS  read-only
STATUS      current
DESCRIPTION
"High IRMS Status
Values:
inactive(0),
active(1)
"
 ::= { ne843InvEntry  45 }

ne843InvEntryIof1 OBJECT-TYPE
SYNTAX      INTEGER {
inactive(0),
active(1)
}
MAX-ACCESS  read-only
STATUS      current
DESCRIPTION
"Output Fuse Status
Values:
inactive(0),
active(1)
"
 ::= { ne843InvEntry  46 }



--
-- object ne843Rpt1
--

ne843Rpt1 OBJECT IDENTIFIER  ::= { ne843  44 }

ne843Rpt1Ide OBJECT-TYPE
SYNTAX      DisplayString
MAX-ACCESS  read-only
STATUS      current
DESCRIPTION
"Identifier"
 ::= { ne843Rpt1  1 }

ne843Rpt1Des OBJECT-TYPE
SYNTAX      DisplayString
MAX-ACCESS  read-write
STATUS      current
DESCRIPTION
"Description"
 ::= { ne843Rpt1  2 }

ne843Rpt1Ena OBJECT-TYPE
SYNTAX      INTEGER {
disable(0),
enable(1)
}
MAX-ACCESS  read-write
STATUS      current
DESCRIPTION
"Enable
Values:
disable(0),
enable(1)
"
 ::= { ne843Rpt1  3 }

ne843Rpt1Int OBJECT-TYPE
SYNTAX      Integer32(1..60)
UNITS       "minutes"
MAX-ACCESS  read-write
STATUS      current
DESCRIPTION
"Interval (minutes)"
 ::= { ne843Rpt1  4 }

ne843Rpt1D001 OBJECT-TYPE
SYNTAX      DisplayString
MAX-ACCESS  read-write
STATUS      current
DESCRIPTION
"Parameter 1"
 ::= { ne843Rpt1  5 }

ne843Rpt1D002 OBJECT-TYPE
SYNTAX      DisplayString
MAX-ACCESS  read-write
STATUS      current
DESCRIPTION
"Parameter 2"
 ::= { ne843Rpt1  6 }

ne843Rpt1D003 OBJECT-TYPE
SYNTAX      DisplayString
MAX-ACCESS  read-write
STATUS      current
DESCRIPTION
"Parameter 3"
 ::= { ne843Rpt1  7 }

ne843Rpt1D004 OBJECT-TYPE
SYNTAX      DisplayString
MAX-ACCESS  read-write
STATUS      current
DESCRIPTION
"Parameter 4"
 ::= { ne843Rpt1  8 }

ne843Rpt1D005 OBJECT-TYPE
SYNTAX      DisplayString
MAX-ACCESS  read-write
STATUS      current
DESCRIPTION
"Parameter 5"
 ::= { ne843Rpt1  9 }

ne843Rpt1D006 OBJECT-TYPE
SYNTAX      DisplayString
MAX-ACCESS  read-write
STATUS      current
DESCRIPTION
"Parameter 6"
 ::= { ne843Rpt1  10 }

ne843Rpt1D007 OBJECT-TYPE
SYNTAX      DisplayString
MAX-ACCESS  read-write
STATUS      current
DESCRIPTION
"Parameter 7"
 ::= { ne843Rpt1  11 }

ne843Rpt1D008 OBJECT-TYPE
SYNTAX      DisplayString
MAX-ACCESS  read-write
STATUS      current
DESCRIPTION
"Parameter 8"
 ::= { ne843Rpt1  12 }

ne843Rpt1D009 OBJECT-TYPE
SYNTAX      DisplayString
MAX-ACCESS  read-write
STATUS      current
DESCRIPTION
"Parameter 9"
 ::= { ne843Rpt1  13 }

ne843Rpt1D010 OBJECT-TYPE
SYNTAX      DisplayString
MAX-ACCESS  read-write
STATUS      current
DESCRIPTION
"Parameter 10"
 ::= { ne843Rpt1  14 }

ne843Rpt1D011 OBJECT-TYPE
SYNTAX      DisplayString
MAX-ACCESS  read-write
STATUS      current
DESCRIPTION
"Parameter 11"
 ::= { ne843Rpt1  15 }

ne843Rpt1D012 OBJECT-TYPE
SYNTAX      DisplayString
MAX-ACCESS  read-write
STATUS      current
DESCRIPTION
"Parameter 12"
 ::= { ne843Rpt1  16 }

ne843Rpt1D013 OBJECT-TYPE
SYNTAX      DisplayString
MAX-ACCESS  read-write
STATUS      current
DESCRIPTION
"Parameter 13"
 ::= { ne843Rpt1  17 }

ne843Rpt1D014 OBJECT-TYPE
SYNTAX      DisplayString
MAX-ACCESS  read-write
STATUS      current
DESCRIPTION
"Parameter 14"
 ::= { ne843Rpt1  18 }

ne843Rpt1D015 OBJECT-TYPE
SYNTAX      DisplayString
MAX-ACCESS  read-write
STATUS      current
DESCRIPTION
"Parameter 15"
 ::= { ne843Rpt1  19 }

ne843Rpt1D016 OBJECT-TYPE
SYNTAX      DisplayString
MAX-ACCESS  read-write
STATUS      current
DESCRIPTION
"Parameter 16"
 ::= { ne843Rpt1  20 }

ne843Rpt1D017 OBJECT-TYPE
SYNTAX      DisplayString
MAX-ACCESS  read-write
STATUS      current
DESCRIPTION
"Parameter 17"
 ::= { ne843Rpt1  21 }

ne843Rpt1D018 OBJECT-TYPE
SYNTAX      DisplayString
MAX-ACCESS  read-write
STATUS      current
DESCRIPTION
"Parameter 18"
 ::= { ne843Rpt1  22 }

ne843Rpt1D019 OBJECT-TYPE
SYNTAX      DisplayString
MAX-ACCESS  read-write
STATUS      current
DESCRIPTION
"Parameter 19"
 ::= { ne843Rpt1  23 }

ne843Rpt1D020 OBJECT-TYPE
SYNTAX      DisplayString
MAX-ACCESS  read-write
STATUS      current
DESCRIPTION
"Parameter 20"
 ::= { ne843Rpt1  24 }

ne843Rpt1D021 OBJECT-TYPE
SYNTAX      DisplayString
MAX-ACCESS  read-write
STATUS      current
DESCRIPTION
"Parameter 21"
 ::= { ne843Rpt1  25 }

ne843Rpt1D022 OBJECT-TYPE
SYNTAX      DisplayString
MAX-ACCESS  read-write
STATUS      current
DESCRIPTION
"Parameter 22"
 ::= { ne843Rpt1  26 }

ne843Rpt1D023 OBJECT-TYPE
SYNTAX      DisplayString
MAX-ACCESS  read-write
STATUS      current
DESCRIPTION
"Parameter 23"
 ::= { ne843Rpt1  27 }

ne843Rpt1D024 OBJECT-TYPE
SYNTAX      DisplayString
MAX-ACCESS  read-write
STATUS      current
DESCRIPTION
"Parameter 24"
 ::= { ne843Rpt1  28 }

ne843Rpt1D025 OBJECT-TYPE
SYNTAX      DisplayString
MAX-ACCESS  read-write
STATUS      current
DESCRIPTION
"Parameter 25"
 ::= { ne843Rpt1  29 }

ne843Rpt1D026 OBJECT-TYPE
SYNTAX      DisplayString
MAX-ACCESS  read-write
STATUS      current
DESCRIPTION
"Parameter 26"
 ::= { ne843Rpt1  30 }

ne843Rpt1D027 OBJECT-TYPE
SYNTAX      DisplayString
MAX-ACCESS  read-write
STATUS      current
DESCRIPTION
"Parameter 27"
 ::= { ne843Rpt1  31 }

ne843Rpt1D028 OBJECT-TYPE
SYNTAX      DisplayString
MAX-ACCESS  read-write
STATUS      current
DESCRIPTION
"Parameter 28"
 ::= { ne843Rpt1  32 }

ne843Rpt1D029 OBJECT-TYPE
SYNTAX      DisplayString
MAX-ACCESS  read-write
STATUS      current
DESCRIPTION
"Parameter 29"
 ::= { ne843Rpt1  33 }

ne843Rpt1D030 OBJECT-TYPE
SYNTAX      DisplayString
MAX-ACCESS  read-write
STATUS      current
DESCRIPTION
"Parameter 30"
 ::= { ne843Rpt1  34 }

ne843Rpt1D031 OBJECT-TYPE
SYNTAX      DisplayString
MAX-ACCESS  read-write
STATUS      current
DESCRIPTION
"Parameter 31"
 ::= { ne843Rpt1  35 }

ne843Rpt1D032 OBJECT-TYPE
SYNTAX      DisplayString
MAX-ACCESS  read-write
STATUS      current
DESCRIPTION
"Parameter 32"
 ::= { ne843Rpt1  36 }

ne843Rpt1D033 OBJECT-TYPE
SYNTAX      DisplayString
MAX-ACCESS  read-write
STATUS      current
DESCRIPTION
"Parameter 33"
 ::= { ne843Rpt1  37 }

ne843Rpt1D034 OBJECT-TYPE
SYNTAX      DisplayString
MAX-ACCESS  read-write
STATUS      current
DESCRIPTION
"Parameter 34"
 ::= { ne843Rpt1  38 }

ne843Rpt1D035 OBJECT-TYPE
SYNTAX      DisplayString
MAX-ACCESS  read-write
STATUS      current
DESCRIPTION
"Parameter 35"
 ::= { ne843Rpt1  39 }

ne843Rpt1D036 OBJECT-TYPE
SYNTAX      DisplayString
MAX-ACCESS  read-write
STATUS      current
DESCRIPTION
"Parameter 36"
 ::= { ne843Rpt1  40 }

ne843Rpt1D037 OBJECT-TYPE
SYNTAX      DisplayString
MAX-ACCESS  read-write
STATUS      current
DESCRIPTION
"Parameter 37"
 ::= { ne843Rpt1  41 }

ne843Rpt1D038 OBJECT-TYPE
SYNTAX      DisplayString
MAX-ACCESS  read-write
STATUS      current
DESCRIPTION
"Parameter 38"
 ::= { ne843Rpt1  42 }

ne843Rpt1D039 OBJECT-TYPE
SYNTAX      DisplayString
MAX-ACCESS  read-write
STATUS      current
DESCRIPTION
"Parameter 39"
 ::= { ne843Rpt1  43 }

ne843Rpt1D040 OBJECT-TYPE
SYNTAX      DisplayString
MAX-ACCESS  read-write
STATUS      current
DESCRIPTION
"Parameter 40"
 ::= { ne843Rpt1  44 }

ne843Rpt1D041 OBJECT-TYPE
SYNTAX      DisplayString
MAX-ACCESS  read-write
STATUS      current
DESCRIPTION
"Parameter 41"
 ::= { ne843Rpt1  45 }

ne843Rpt1D042 OBJECT-TYPE
SYNTAX      DisplayString
MAX-ACCESS  read-write
STATUS      current
DESCRIPTION
"Parameter 42"
 ::= { ne843Rpt1  46 }

ne843Rpt1D043 OBJECT-TYPE
SYNTAX      DisplayString
MAX-ACCESS  read-write
STATUS      current
DESCRIPTION
"Parameter 43"
 ::= { ne843Rpt1  47 }

ne843Rpt1D044 OBJECT-TYPE
SYNTAX      DisplayString
MAX-ACCESS  read-write
STATUS      current
DESCRIPTION
"Parameter 44"
 ::= { ne843Rpt1  48 }

ne843Rpt1D045 OBJECT-TYPE
SYNTAX      DisplayString
MAX-ACCESS  read-write
STATUS      current
DESCRIPTION
"Parameter 45"
 ::= { ne843Rpt1  49 }

ne843Rpt1D046 OBJECT-TYPE
SYNTAX      DisplayString
MAX-ACCESS  read-write
STATUS      current
DESCRIPTION
"Parameter 46"
 ::= { ne843Rpt1  50 }

ne843Rpt1D047 OBJECT-TYPE
SYNTAX      DisplayString
MAX-ACCESS  read-write
STATUS      current
DESCRIPTION
"Parameter 47"
 ::= { ne843Rpt1  51 }

ne843Rpt1D048 OBJECT-TYPE
SYNTAX      DisplayString
MAX-ACCESS  read-write
STATUS      current
DESCRIPTION
"Parameter 48"
 ::= { ne843Rpt1  52 }

ne843Rpt1D049 OBJECT-TYPE
SYNTAX      DisplayString
MAX-ACCESS  read-write
STATUS      current
DESCRIPTION
"Parameter 49"
 ::= { ne843Rpt1  53 }

ne843Rpt1D050 OBJECT-TYPE
SYNTAX      DisplayString
MAX-ACCESS  read-write
STATUS      current
DESCRIPTION
"Parameter 40"
 ::= { ne843Rpt1  54 }

ne843Rpt1D051 OBJECT-TYPE
SYNTAX      DisplayString
MAX-ACCESS  read-write
STATUS      current
DESCRIPTION
"Parameter 51"
 ::= { ne843Rpt1  55 }

ne843Rpt1D052 OBJECT-TYPE
SYNTAX      DisplayString
MAX-ACCESS  read-write
STATUS      current
DESCRIPTION
"Parameter 52"
 ::= { ne843Rpt1  56 }

ne843Rpt1D053 OBJECT-TYPE
SYNTAX      DisplayString
MAX-ACCESS  read-write
STATUS      current
DESCRIPTION
"Parameter 53"
 ::= { ne843Rpt1  57 }

ne843Rpt1D054 OBJECT-TYPE
SYNTAX      DisplayString
MAX-ACCESS  read-write
STATUS      current
DESCRIPTION
"Parameter 54"
 ::= { ne843Rpt1  58 }

ne843Rpt1D055 OBJECT-TYPE
SYNTAX      DisplayString
MAX-ACCESS  read-write
STATUS      current
DESCRIPTION
"Parameter 55"
 ::= { ne843Rpt1  59 }

ne843Rpt1D056 OBJECT-TYPE
SYNTAX      DisplayString
MAX-ACCESS  read-write
STATUS      current
DESCRIPTION
"Parameter 56"
 ::= { ne843Rpt1  60 }

ne843Rpt1D057 OBJECT-TYPE
SYNTAX      DisplayString
MAX-ACCESS  read-write
STATUS      current
DESCRIPTION
"Parameter 57"
 ::= { ne843Rpt1  61 }

ne843Rpt1D058 OBJECT-TYPE
SYNTAX      DisplayString
MAX-ACCESS  read-write
STATUS      current
DESCRIPTION
"Parameter 58"
 ::= { ne843Rpt1  62 }

ne843Rpt1D059 OBJECT-TYPE
SYNTAX      DisplayString
MAX-ACCESS  read-write
STATUS      current
DESCRIPTION
"Parameter 59"
 ::= { ne843Rpt1  63 }

ne843Rpt1D060 OBJECT-TYPE
SYNTAX      DisplayString
MAX-ACCESS  read-write
STATUS      current
DESCRIPTION
"Parameter 60"
 ::= { ne843Rpt1  64 }

ne843Rpt1D061 OBJECT-TYPE
SYNTAX      DisplayString
MAX-ACCESS  read-write
STATUS      current
DESCRIPTION
"Parameter 61"
 ::= { ne843Rpt1  65 }

ne843Rpt1D062 OBJECT-TYPE
SYNTAX      DisplayString
MAX-ACCESS  read-write
STATUS      current
DESCRIPTION
"Parameter 62"
 ::= { ne843Rpt1  66 }

ne843Rpt1D063 OBJECT-TYPE
SYNTAX      DisplayString
MAX-ACCESS  read-write
STATUS      current
DESCRIPTION
"Parameter 63"
 ::= { ne843Rpt1  67 }

ne843Rpt1D064 OBJECT-TYPE
SYNTAX      DisplayString
MAX-ACCESS  read-write
STATUS      current
DESCRIPTION
"Parameter 64"
 ::= { ne843Rpt1  68 }

ne843Rpt1D065 OBJECT-TYPE
SYNTAX      DisplayString
MAX-ACCESS  read-write
STATUS      current
DESCRIPTION
"Parameter 65"
 ::= { ne843Rpt1  69 }

ne843Rpt1D066 OBJECT-TYPE
SYNTAX      DisplayString
MAX-ACCESS  read-write
STATUS      current
DESCRIPTION
"Parameter 66"
 ::= { ne843Rpt1  70 }

ne843Rpt1D067 OBJECT-TYPE
SYNTAX      DisplayString
MAX-ACCESS  read-write
STATUS      current
DESCRIPTION
"Parameter 67"
 ::= { ne843Rpt1  71 }

ne843Rpt1D068 OBJECT-TYPE
SYNTAX      DisplayString
MAX-ACCESS  read-write
STATUS      current
DESCRIPTION
"Parameter 68"
 ::= { ne843Rpt1  72 }

ne843Rpt1D069 OBJECT-TYPE
SYNTAX      DisplayString
MAX-ACCESS  read-write
STATUS      current
DESCRIPTION
"Parameter 69"
 ::= { ne843Rpt1  73 }

ne843Rpt1D070 OBJECT-TYPE
SYNTAX      DisplayString
MAX-ACCESS  read-write
STATUS      current
DESCRIPTION
"Parameter 70"
 ::= { ne843Rpt1  74 }

ne843Rpt1D071 OBJECT-TYPE
SYNTAX      DisplayString
MAX-ACCESS  read-write
STATUS      current
DESCRIPTION
"Parameter 71"
 ::= { ne843Rpt1  75 }

ne843Rpt1D072 OBJECT-TYPE
SYNTAX      DisplayString
MAX-ACCESS  read-write
STATUS      current
DESCRIPTION
"Parameter 72"
 ::= { ne843Rpt1  76 }

ne843Rpt1D073 OBJECT-TYPE
SYNTAX      DisplayString
MAX-ACCESS  read-write
STATUS      current
DESCRIPTION
"Parameter 73"
 ::= { ne843Rpt1  77 }

ne843Rpt1D074 OBJECT-TYPE
SYNTAX      DisplayString
MAX-ACCESS  read-write
STATUS      current
DESCRIPTION
"Parameter 74"
 ::= { ne843Rpt1  78 }

ne843Rpt1D075 OBJECT-TYPE
SYNTAX      DisplayString
MAX-ACCESS  read-write
STATUS      current
DESCRIPTION
"Parameter 75"
 ::= { ne843Rpt1  79 }

ne843Rpt1D076 OBJECT-TYPE
SYNTAX      DisplayString
MAX-ACCESS  read-write
STATUS      current
DESCRIPTION
"Parameter 76"
 ::= { ne843Rpt1  80 }

ne843Rpt1D077 OBJECT-TYPE
SYNTAX      DisplayString
MAX-ACCESS  read-write
STATUS      current
DESCRIPTION
"Parameter 77"
 ::= { ne843Rpt1  81 }

ne843Rpt1D078 OBJECT-TYPE
SYNTAX      DisplayString
MAX-ACCESS  read-write
STATUS      current
DESCRIPTION
"Parameter 78"
 ::= { ne843Rpt1  82 }

ne843Rpt1D079 OBJECT-TYPE
SYNTAX      DisplayString
MAX-ACCESS  read-write
STATUS      current
DESCRIPTION
"Parameter 79"
 ::= { ne843Rpt1  83 }

ne843Rpt1D080 OBJECT-TYPE
SYNTAX      DisplayString
MAX-ACCESS  read-write
STATUS      current
DESCRIPTION
"Parameter 80"
 ::= { ne843Rpt1  84 }

ne843Rpt1D081 OBJECT-TYPE
SYNTAX      DisplayString
MAX-ACCESS  read-write
STATUS      current
DESCRIPTION
"Parameter 81"
 ::= { ne843Rpt1  85 }

ne843Rpt1D082 OBJECT-TYPE
SYNTAX      DisplayString
MAX-ACCESS  read-write
STATUS      current
DESCRIPTION
"Parameter 82"
 ::= { ne843Rpt1  86 }

ne843Rpt1D083 OBJECT-TYPE
SYNTAX      DisplayString
MAX-ACCESS  read-write
STATUS      current
DESCRIPTION
"Parameter 83"
 ::= { ne843Rpt1  87 }

ne843Rpt1D084 OBJECT-TYPE
SYNTAX      DisplayString
MAX-ACCESS  read-write
STATUS      current
DESCRIPTION
"Parameter 84"
 ::= { ne843Rpt1  88 }

ne843Rpt1D085 OBJECT-TYPE
SYNTAX      DisplayString
MAX-ACCESS  read-write
STATUS      current
DESCRIPTION
"Parameter 85"
 ::= { ne843Rpt1  89 }

ne843Rpt1D086 OBJECT-TYPE
SYNTAX      DisplayString
MAX-ACCESS  read-write
STATUS      current
DESCRIPTION
"Parameter 86"
 ::= { ne843Rpt1  90 }

ne843Rpt1D087 OBJECT-TYPE
SYNTAX      DisplayString
MAX-ACCESS  read-write
STATUS      current
DESCRIPTION
"Parameter 87"
 ::= { ne843Rpt1  91 }

ne843Rpt1D088 OBJECT-TYPE
SYNTAX      DisplayString
MAX-ACCESS  read-write
STATUS      current
DESCRIPTION
"Parameter 88"
 ::= { ne843Rpt1  92 }

ne843Rpt1D089 OBJECT-TYPE
SYNTAX      DisplayString
MAX-ACCESS  read-write
STATUS      current
DESCRIPTION
"Parameter 89"
 ::= { ne843Rpt1  93 }

ne843Rpt1D090 OBJECT-TYPE
SYNTAX      DisplayString
MAX-ACCESS  read-write
STATUS      current
DESCRIPTION
"Parameter 90"
 ::= { ne843Rpt1  94 }

ne843Rpt1D091 OBJECT-TYPE
SYNTAX      DisplayString
MAX-ACCESS  read-write
STATUS      current
DESCRIPTION
"Parameter 91"
 ::= { ne843Rpt1  95 }

ne843Rpt1D092 OBJECT-TYPE
SYNTAX      DisplayString
MAX-ACCESS  read-write
STATUS      current
DESCRIPTION
"Parameter 92"
 ::= { ne843Rpt1  96 }

ne843Rpt1D093 OBJECT-TYPE
SYNTAX      DisplayString
MAX-ACCESS  read-write
STATUS      current
DESCRIPTION
"Parameter 93"
 ::= { ne843Rpt1  97 }

ne843Rpt1D094 OBJECT-TYPE
SYNTAX      DisplayString
MAX-ACCESS  read-write
STATUS      current
DESCRIPTION
"Parameter 94"
 ::= { ne843Rpt1  98 }

ne843Rpt1D095 OBJECT-TYPE
SYNTAX      DisplayString
MAX-ACCESS  read-write
STATUS      current
DESCRIPTION
"Parameter 95"
 ::= { ne843Rpt1  99 }

ne843Rpt1D096 OBJECT-TYPE
SYNTAX      DisplayString
MAX-ACCESS  read-write
STATUS      current
DESCRIPTION
"Parameter 96"
 ::= { ne843Rpt1  100 }

ne843Rpt1D097 OBJECT-TYPE
SYNTAX      DisplayString
MAX-ACCESS  read-write
STATUS      current
DESCRIPTION
"Parameter 97"
 ::= { ne843Rpt1  101 }

ne843Rpt1D098 OBJECT-TYPE
SYNTAX      DisplayString
MAX-ACCESS  read-write
STATUS      current
DESCRIPTION
"Parameter 98"
 ::= { ne843Rpt1  102 }

ne843Rpt1D099 OBJECT-TYPE
SYNTAX      DisplayString
MAX-ACCESS  read-write
STATUS      current
DESCRIPTION
"Parameter 99"
 ::= { ne843Rpt1  103 }

ne843Rpt1D100 OBJECT-TYPE
SYNTAX      DisplayString
MAX-ACCESS  read-write
STATUS      current
DESCRIPTION
"Parameter 100"
 ::= { ne843Rpt1  104 }

ne843Rpt1D101 OBJECT-TYPE
SYNTAX      DisplayString
MAX-ACCESS  read-write
STATUS      current
DESCRIPTION
"Parameter 101"
 ::= { ne843Rpt1  105 }

ne843Rpt1D102 OBJECT-TYPE
SYNTAX      DisplayString
MAX-ACCESS  read-write
STATUS      current
DESCRIPTION
"Parameter 102"
 ::= { ne843Rpt1  106 }

ne843Rpt1D103 OBJECT-TYPE
SYNTAX      DisplayString
MAX-ACCESS  read-write
STATUS      current
DESCRIPTION
"Parameter 103"
 ::= { ne843Rpt1  107 }

ne843Rpt1D104 OBJECT-TYPE
SYNTAX      DisplayString
MAX-ACCESS  read-write
STATUS      current
DESCRIPTION
"Parameter 104"
 ::= { ne843Rpt1  108 }

ne843Rpt1D105 OBJECT-TYPE
SYNTAX      DisplayString
MAX-ACCESS  read-write
STATUS      current
DESCRIPTION
"Parameter 105"
 ::= { ne843Rpt1  109 }

ne843Rpt1D106 OBJECT-TYPE
SYNTAX      DisplayString
MAX-ACCESS  read-write
STATUS      current
DESCRIPTION
"Parameter 106"
 ::= { ne843Rpt1  110 }

ne843Rpt1D107 OBJECT-TYPE
SYNTAX      DisplayString
MAX-ACCESS  read-write
STATUS      current
DESCRIPTION
"Parameter 107"
 ::= { ne843Rpt1  111 }

ne843Rpt1D108 OBJECT-TYPE
SYNTAX      DisplayString
MAX-ACCESS  read-write
STATUS      current
DESCRIPTION
"Parameter 108"
 ::= { ne843Rpt1  112 }

ne843Rpt1D109 OBJECT-TYPE
SYNTAX      DisplayString
MAX-ACCESS  read-write
STATUS      current
DESCRIPTION
"Parameter 109"
 ::= { ne843Rpt1  113 }

ne843Rpt1D110 OBJECT-TYPE
SYNTAX      DisplayString
MAX-ACCESS  read-write
STATUS      current
DESCRIPTION
"Parameter 110"
 ::= { ne843Rpt1  114 }

ne843Rpt1D111 OBJECT-TYPE
SYNTAX      DisplayString
MAX-ACCESS  read-write
STATUS      current
DESCRIPTION
"Parameter 111"
 ::= { ne843Rpt1  115 }

ne843Rpt1D112 OBJECT-TYPE
SYNTAX      DisplayString
MAX-ACCESS  read-write
STATUS      current
DESCRIPTION
"Parameter 112"
 ::= { ne843Rpt1  116 }

ne843Rpt1D113 OBJECT-TYPE
SYNTAX      DisplayString
MAX-ACCESS  read-write
STATUS      current
DESCRIPTION
"Parameter 113"
 ::= { ne843Rpt1  117 }

ne843Rpt1D114 OBJECT-TYPE
SYNTAX      DisplayString
MAX-ACCESS  read-write
STATUS      current
DESCRIPTION
"Parameter 114"
 ::= { ne843Rpt1  118 }

ne843Rpt1D115 OBJECT-TYPE
SYNTAX      DisplayString
MAX-ACCESS  read-write
STATUS      current
DESCRIPTION
"Parameter 115"
 ::= { ne843Rpt1  119 }

ne843Rpt1D116 OBJECT-TYPE
SYNTAX      DisplayString
MAX-ACCESS  read-write
STATUS      current
DESCRIPTION
"Parameter 116"
 ::= { ne843Rpt1  120 }

ne843Rpt1D117 OBJECT-TYPE
SYNTAX      DisplayString
MAX-ACCESS  read-write
STATUS      current
DESCRIPTION
"Parameter 117"
 ::= { ne843Rpt1  121 }

ne843Rpt1D118 OBJECT-TYPE
SYNTAX      DisplayString
MAX-ACCESS  read-write
STATUS      current
DESCRIPTION
"Parameter 118"
 ::= { ne843Rpt1  122 }

ne843Rpt1D119 OBJECT-TYPE
SYNTAX      DisplayString
MAX-ACCESS  read-write
STATUS      current
DESCRIPTION
"Parameter 119"
 ::= { ne843Rpt1  123 }

ne843Rpt1D120 OBJECT-TYPE
SYNTAX      DisplayString
MAX-ACCESS  read-write
STATUS      current
DESCRIPTION
"Parameter 120"
 ::= { ne843Rpt1  124 }

ne843Rpt1D121 OBJECT-TYPE
SYNTAX      DisplayString
MAX-ACCESS  read-write
STATUS      current
DESCRIPTION
"Parameter 121"
 ::= { ne843Rpt1  125 }

ne843Rpt1D122 OBJECT-TYPE
SYNTAX      DisplayString
MAX-ACCESS  read-write
STATUS      current
DESCRIPTION
"Parameter 122"
 ::= { ne843Rpt1  126 }

ne843Rpt1D123 OBJECT-TYPE
SYNTAX      DisplayString
MAX-ACCESS  read-write
STATUS      current
DESCRIPTION
"Parameter 123"
 ::= { ne843Rpt1  127 }

ne843Rpt1D124 OBJECT-TYPE
SYNTAX      DisplayString
MAX-ACCESS  read-write
STATUS      current
DESCRIPTION
"Parameter 124"
 ::= { ne843Rpt1  128 }

ne843Rpt1D125 OBJECT-TYPE
SYNTAX      DisplayString
MAX-ACCESS  read-write
STATUS      current
DESCRIPTION
"Parameter 125"
 ::= { ne843Rpt1  129 }

ne843Rpt1D126 OBJECT-TYPE
SYNTAX      DisplayString
MAX-ACCESS  read-write
STATUS      current
DESCRIPTION
"Parameter 126"
 ::= { ne843Rpt1  130 }

ne843Rpt1D127 OBJECT-TYPE
SYNTAX      DisplayString
MAX-ACCESS  read-write
STATUS      current
DESCRIPTION
"Parameter 127"
 ::= { ne843Rpt1  131 }

ne843Rpt1D128 OBJECT-TYPE
SYNTAX      DisplayString
MAX-ACCESS  read-write
STATUS      current
DESCRIPTION
"Parameter 128"
 ::= { ne843Rpt1  132 }

ne843Rpt1D129 OBJECT-TYPE
SYNTAX      DisplayString
MAX-ACCESS  read-write
STATUS      current
DESCRIPTION
"Parameter 129"
 ::= { ne843Rpt1  133 }

ne843Rpt1D130 OBJECT-TYPE
SYNTAX      DisplayString
MAX-ACCESS  read-write
STATUS      current
DESCRIPTION
"Parameter 130"
 ::= { ne843Rpt1  134 }

ne843Rpt1D131 OBJECT-TYPE
SYNTAX      DisplayString
MAX-ACCESS  read-write
STATUS      current
DESCRIPTION
"Parameter 131"
 ::= { ne843Rpt1  135 }

ne843Rpt1D132 OBJECT-TYPE
SYNTAX      DisplayString
MAX-ACCESS  read-write
STATUS      current
DESCRIPTION
"Parameter 132"
 ::= { ne843Rpt1  136 }

ne843Rpt1D133 OBJECT-TYPE
SYNTAX      DisplayString
MAX-ACCESS  read-write
STATUS      current
DESCRIPTION
"Parameter 133"
 ::= { ne843Rpt1  137 }

ne843Rpt1D134 OBJECT-TYPE
SYNTAX      DisplayString
MAX-ACCESS  read-write
STATUS      current
DESCRIPTION
"Parameter 134"
 ::= { ne843Rpt1  138 }

ne843Rpt1D135 OBJECT-TYPE
SYNTAX      DisplayString
MAX-ACCESS  read-write
STATUS      current
DESCRIPTION
"Parameter 135"
 ::= { ne843Rpt1  139 }

ne843Rpt1D136 OBJECT-TYPE
SYNTAX      DisplayString
MAX-ACCESS  read-write
STATUS      current
DESCRIPTION
"Parameter 136"
 ::= { ne843Rpt1  140 }

ne843Rpt1D137 OBJECT-TYPE
SYNTAX      DisplayString
MAX-ACCESS  read-write
STATUS      current
DESCRIPTION
"Parameter 137"
 ::= { ne843Rpt1  141 }

ne843Rpt1D138 OBJECT-TYPE
SYNTAX      DisplayString
MAX-ACCESS  read-write
STATUS      current
DESCRIPTION
"Parameter 138"
 ::= { ne843Rpt1  142 }

ne843Rpt1D139 OBJECT-TYPE
SYNTAX      DisplayString
MAX-ACCESS  read-write
STATUS      current
DESCRIPTION
"Parameter 139"
 ::= { ne843Rpt1  143 }

ne843Rpt1D140 OBJECT-TYPE
SYNTAX      DisplayString
MAX-ACCESS  read-write
STATUS      current
DESCRIPTION
"Parameter 140"
 ::= { ne843Rpt1  144 }

ne843Rpt1D141 OBJECT-TYPE
SYNTAX      DisplayString
MAX-ACCESS  read-write
STATUS      current
DESCRIPTION
"Parameter 141"
 ::= { ne843Rpt1  145 }

ne843Rpt1D142 OBJECT-TYPE
SYNTAX      DisplayString
MAX-ACCESS  read-write
STATUS      current
DESCRIPTION
"Parameter 142"
 ::= { ne843Rpt1  146 }

ne843Rpt1D143 OBJECT-TYPE
SYNTAX      DisplayString
MAX-ACCESS  read-write
STATUS      current
DESCRIPTION
"Parameter 143"
 ::= { ne843Rpt1  147 }

ne843Rpt1D144 OBJECT-TYPE
SYNTAX      DisplayString
MAX-ACCESS  read-write
STATUS      current
DESCRIPTION
"Parameter 144"
 ::= { ne843Rpt1  148 }

ne843Rpt1D145 OBJECT-TYPE
SYNTAX      DisplayString
MAX-ACCESS  read-write
STATUS      current
DESCRIPTION
"Parameter 145"
 ::= { ne843Rpt1  149 }

ne843Rpt1D146 OBJECT-TYPE
SYNTAX      DisplayString
MAX-ACCESS  read-write
STATUS      current
DESCRIPTION
"Parameter 146"
 ::= { ne843Rpt1  150 }

ne843Rpt1D147 OBJECT-TYPE
SYNTAX      DisplayString
MAX-ACCESS  read-write
STATUS      current
DESCRIPTION
"Parameter 147"
 ::= { ne843Rpt1  151 }

ne843Rpt1D148 OBJECT-TYPE
SYNTAX      DisplayString
MAX-ACCESS  read-write
STATUS      current
DESCRIPTION
"Parameter 148"
 ::= { ne843Rpt1  152 }

ne843Rpt1D149 OBJECT-TYPE
SYNTAX      DisplayString
MAX-ACCESS  read-write
STATUS      current
DESCRIPTION
"Parameter 149"
 ::= { ne843Rpt1  153 }

ne843Rpt1D150 OBJECT-TYPE
SYNTAX      DisplayString
MAX-ACCESS  read-write
STATUS      current
DESCRIPTION
"Parameter 150"
 ::= { ne843Rpt1  154 }


--
-- table PIC
--

ne843PicTable    OBJECT-TYPE
SYNTAX SEQUENCE OF Ne843PicEntry
MAX-ACCESS not-accessible
STATUS current
DESCRIPTION
        "Table of all Panel Interface Card data"
 ::= { ne843  45 }

ne843PicEntry OBJECT-TYPE
SYNTAX     Ne843PicEntry
MAX-ACCESS  not-accessible
STATUS      current
DESCRIPTION
       "Entry of information for one Panel Interface Card"
INDEX { ne843PicEntryIndex }
 ::= { ne843PicTable  1 }

Ne843PicEntry ::= SEQUENCE {
ne843PicEntryIndex   INTEGER,
ne843PicEntryIde   DisplayString,
ne843PicEntryDes   DisplayString,
ne843PicEntrySn   DisplayString,
ne843PicEntryCc   DisplayString,
ne843PicEntrySer   DisplayString,
ne843PicEntryClei   DisplayString,
ne843PicEntryCustpn2   DisplayString,
ne843PicEntryAsstag2   DisplayString,
ne843PicEntryStt   DisplayString,
ne843PicEntryTyp   DisplayString,
ne843PicEntryNst   Integer32,
ne843PicEntryNvt   Integer32,
ne843PicEntryVera   DisplayString,
ne843PicEntryPid   DisplayString,
ne843PicEntryPcf   DisplayString,
ne843PicEntryNumslot   Integer32,
ne843PicEntryCbf   DisplayString,
ne843PicEntryFajae   INTEGER,
ne843PicEntryFajrly   DisplayString,
ne843PicEntryOsae   INTEGER,
ne843PicEntryOsarly   DisplayString,
ne843PicEntryTmpe   INTEGER,
ne843PicEntryTmprly   DisplayString,
ne843PicEntryVlvs   DisplayString,
ne843PicEntryVlvlat   DisplayString,
ne843PicEntryVlvae   INTEGER,
ne843PicEntryVlvath   Integer32,
ne843PicEntryVlvbe   INTEGER,
ne843PicEntryVlvbth   Integer32,
ne843PicEntryVlvrly   DisplayString,
ne843PicEntryOvls   DisplayString,
ne843PicEntryOlvlat   DisplayString,
ne843PicEntryOvlae   INTEGER,
ne843PicEntryOvlath   Integer32,
ne843PicEntryOvlbe   INTEGER,
ne843PicEntryOvlbth   Integer32,
ne843PicEntryOvlrly   DisplayString,
ne843PicEntryEpoe   INTEGER,
ne843PicEntryEporly   DisplayString,
ne843PicEntryPcauxe   INTEGER,
ne843PicEntryPcauxr   DisplayString,
ne843PicEntrySlote   INTEGER,
ne843PicEntrySlotrly   DisplayString,
ne843PicEntryDpmode   DisplayString,
ne843PicEntryPnldes   DisplayString,
ne843PicEntryMdl   DisplayString,
ne843PicEntryPnlsn   DisplayString,
ne843PicEntryPnlcc   DisplayString,
ne843PicEntryPnlser   DisplayString,
ne843PicEntryPnlclei   DisplayString,
ne843PicEntryCustpn1   DisplayString,
ne843PicEntryAsstag1   DisplayString,
ne843PicEntryRtng   DisplayString,
ne843PicEntryPnlsize   DisplayString
}

ne843PicEntryIndex OBJECT-TYPE
SYNTAX      INTEGER (0..2147483647)
MAX-ACCESS  read-only
STATUS      current
DESCRIPTION
"Table Index"
 ::= { ne843PicEntry  1 }

ne843PicEntryIde OBJECT-TYPE
SYNTAX      DisplayString
MAX-ACCESS  read-only
STATUS      current
DESCRIPTION
"Identifier"
 ::= { ne843PicEntry  2 }

ne843PicEntryDes OBJECT-TYPE
SYNTAX      DisplayString
MAX-ACCESS  read-write
STATUS      current
DESCRIPTION
"Description"
 ::= { ne843PicEntry  3 }

ne843PicEntrySn OBJECT-TYPE
SYNTAX      DisplayString
MAX-ACCESS  read-only
STATUS      current
DESCRIPTION
"Serial Number"
 ::= { ne843PicEntry  4 }

ne843PicEntryCc OBJECT-TYPE
SYNTAX      DisplayString
MAX-ACCESS  read-only
STATUS      current
DESCRIPTION
"Comcode"
 ::= { ne843PicEntry  5 }

ne843PicEntrySer OBJECT-TYPE
SYNTAX      DisplayString
MAX-ACCESS  read-only
STATUS      current
DESCRIPTION
"Series"
 ::= { ne843PicEntry  6 }

ne843PicEntryClei OBJECT-TYPE
SYNTAX      DisplayString
MAX-ACCESS  read-only
STATUS      current
DESCRIPTION
"Clei Code"
 ::= { ne843PicEntry  7 }

ne843PicEntryCustpn2 OBJECT-TYPE
SYNTAX      DisplayString
MAX-ACCESS  read-only
STATUS      current
DESCRIPTION
"Customer PIC Part Number"
 ::= { ne843PicEntry  8 }

ne843PicEntryAsstag2 OBJECT-TYPE
SYNTAX      DisplayString
MAX-ACCESS  read-only
STATUS      current
DESCRIPTION
"PIC Asset Tag"
 ::= { ne843PicEntry  9 }

ne843PicEntryStt OBJECT-TYPE
SYNTAX      DisplayString
MAX-ACCESS  read-write
STATUS      current
DESCRIPTION
"State
Values:
PRESENT,
MISSING,
VACANT
"
 ::= { ne843PicEntry  10 }

ne843PicEntryTyp OBJECT-TYPE
SYNTAX      DisplayString
MAX-ACCESS  read-write
STATUS      current
DESCRIPTION
"PIC Type
Values:
LOAD,
BATT
"
 ::= { ne843PicEntry  11 }

ne843PicEntryNst OBJECT-TYPE
SYNTAX      Integer32
MAX-ACCESS  read-write
STATUS      current
DESCRIPTION
"Number of Shunts"
 ::= { ne843PicEntry  12 }

ne843PicEntryNvt OBJECT-TYPE
SYNTAX      Integer32
MAX-ACCESS  read-write
STATUS      current
DESCRIPTION
"Number of Voltages"
 ::= { ne843PicEntry  13 }

ne843PicEntryVera OBJECT-TYPE
SYNTAX      DisplayString
MAX-ACCESS  read-only
STATUS      current
DESCRIPTION
"Application Software Version"
 ::= { ne843PicEntry  14 }

ne843PicEntryPid OBJECT-TYPE
SYNTAX      DisplayString
MAX-ACCESS  read-only
STATUS      current
DESCRIPTION
"ID Conflict"
 ::= { ne843PicEntry  15 }

ne843PicEntryPcf OBJECT-TYPE
SYNTAX      DisplayString
MAX-ACCESS  read-only
STATUS      current
DESCRIPTION
"Communication Failure"
 ::= { ne843PicEntry  16 }

ne843PicEntryNumslot OBJECT-TYPE
SYNTAX      Integer32
MAX-ACCESS  read-only
STATUS      current
DESCRIPTION
"Number of Slots"
 ::= { ne843PicEntry  17 }

ne843PicEntryCbf OBJECT-TYPE
SYNTAX      DisplayString
MAX-ACCESS  read-write
STATUS      current
DESCRIPTION
"CB or Fuse
Values:
CB,
FUSE
"
 ::= { ne843PicEntry  18 }

ne843PicEntryFajae OBJECT-TYPE
SYNTAX      INTEGER {
disable(0),
enable(1)
}
MAX-ACCESS  read-write
STATUS      current
DESCRIPTION
"External Fuse Enable
Values:
disable(0),
enable(1)
"
 ::= { ne843PicEntry  19 }

ne843PicEntryFajrly OBJECT-TYPE
SYNTAX      DisplayString
MAX-ACCESS  read-write
STATUS      current
DESCRIPTION
"External Fuse Relay
Values:
None,
Enabled
"
 ::= { ne843PicEntry  20 }

ne843PicEntryOsae OBJECT-TYPE
SYNTAX      INTEGER {
disable(0),
enable(1)
}
MAX-ACCESS  read-write
STATUS      current
DESCRIPTION
"Open String Enable
Values:
disable(0),
enable(1)
"
 ::= { ne843PicEntry  21 }

ne843PicEntryOsarly OBJECT-TYPE
SYNTAX      DisplayString
MAX-ACCESS  read-write
STATUS      current
DESCRIPTION
"Open String Relay
Values:
None,
Enabled
"
 ::= { ne843PicEntry  22 }

ne843PicEntryTmpe OBJECT-TYPE
SYNTAX      INTEGER {
disable(0),
enable(1)
}
MAX-ACCESS  read-write
STATUS      current
DESCRIPTION
"Temperature Enable
Values:
disable(0),
enable(1)
"
 ::= { ne843PicEntry  23 }

ne843PicEntryTmprly OBJECT-TYPE
SYNTAX      DisplayString
MAX-ACCESS  read-write
STATUS      current
DESCRIPTION
"Temperature Relay
Values:
None,
Enabled
"
 ::= { ne843PicEntry  24 }

ne843PicEntryVlvs OBJECT-TYPE
SYNTAX      DisplayString
MAX-ACCESS  read-write
STATUS      current
DESCRIPTION
"Power Loss Severity
Values:
CRIT,
MAJ,
MIN,
WRN,
RO
"
 ::= { ne843PicEntry  25 }

ne843PicEntryVlvlat OBJECT-TYPE
SYNTAX      DisplayString
MAX-ACCESS  read-write
STATUS      current
DESCRIPTION
"Power Loss Latched"
 ::= { ne843PicEntry  26 }

ne843PicEntryVlvae OBJECT-TYPE
SYNTAX      INTEGER {
disable(0),
enable(1)
}
MAX-ACCESS  read-write
STATUS      current
DESCRIPTION
"VA Power Loss Enable
Values:
disable(0),
enable(1)
"
 ::= { ne843PicEntry  27 }

ne843PicEntryVlvath OBJECT-TYPE
SYNTAX      Integer32
MAX-ACCESS  read-write
STATUS      current
DESCRIPTION
"VB Power Loss Threshold"
 ::= { ne843PicEntry  28 }

ne843PicEntryVlvbe OBJECT-TYPE
SYNTAX      INTEGER {
disable(0),
enable(1)
}
MAX-ACCESS  read-write
STATUS      current
DESCRIPTION
"VB Power Loss Enable
Values:
disable(0),
enable(1)
"
 ::= { ne843PicEntry  29 }

ne843PicEntryVlvbth OBJECT-TYPE
SYNTAX      Integer32
MAX-ACCESS  read-write
STATUS      current
DESCRIPTION
"VB Power Loss Threshold"
 ::= { ne843PicEntry  30 }

ne843PicEntryVlvrly OBJECT-TYPE
SYNTAX      DisplayString
MAX-ACCESS  read-write
STATUS      current
DESCRIPTION
"Power Loss Relay
Values:
None,
Enabled
"
 ::= { ne843PicEntry  31 }

ne843PicEntryOvls OBJECT-TYPE
SYNTAX      DisplayString
MAX-ACCESS  read-write
STATUS      current
DESCRIPTION
"Overload Severity
Values:
CRIT,
MAJ,
MIN,
WRN,
RO
"
 ::= { ne843PicEntry  32 }

ne843PicEntryOlvlat OBJECT-TYPE
SYNTAX      DisplayString
MAX-ACCESS  read-write
STATUS      current
DESCRIPTION
"Overload Latched"
 ::= { ne843PicEntry  33 }

ne843PicEntryOvlae OBJECT-TYPE
SYNTAX      INTEGER {
disable(0),
enable(1)
}
MAX-ACCESS  read-write
STATUS      current
DESCRIPTION
"IA Overload Enabled
Values:
disable(0),
enable(1)
"
 ::= { ne843PicEntry  34 }

ne843PicEntryOvlath OBJECT-TYPE
SYNTAX      Integer32
MAX-ACCESS  read-write
STATUS      current
DESCRIPTION
"IA Overload Threshold"
 ::= { ne843PicEntry  35 }

ne843PicEntryOvlbe OBJECT-TYPE
SYNTAX      INTEGER {
disable(0),
enable(1)
}
MAX-ACCESS  read-write
STATUS      current
DESCRIPTION
"IB Overload Enabled
Values:
disable(0),
enable(1)
"
 ::= { ne843PicEntry  36 }

ne843PicEntryOvlbth OBJECT-TYPE
SYNTAX      Integer32
MAX-ACCESS  read-write
STATUS      current
DESCRIPTION
"IB Overload Threshold"
 ::= { ne843PicEntry  37 }

ne843PicEntryOvlrly OBJECT-TYPE
SYNTAX      DisplayString
MAX-ACCESS  read-write
STATUS      current
DESCRIPTION
"Overload Relay
Values:
None,
Enabled
"
 ::= { ne843PicEntry  38 }

ne843PicEntryEpoe OBJECT-TYPE
SYNTAX      INTEGER {
disable(0),
enable(1)
}
MAX-ACCESS  read-write
STATUS      current
DESCRIPTION
"Emergency Power Off Enabled
Values:
disable(0),
enable(1)
"
 ::= { ne843PicEntry  39 }

ne843PicEntryEporly OBJECT-TYPE
SYNTAX      DisplayString
MAX-ACCESS  read-write
STATUS      current
DESCRIPTION
"Emergency Power Off Relay
Values:
None,
Enabled
"
 ::= { ne843PicEntry  40 }

ne843PicEntryPcauxe OBJECT-TYPE
SYNTAX      INTEGER {
disable(0),
enable(1)
}
MAX-ACCESS  read-write
STATUS      current
DESCRIPTION
"PIC Auxiliary Enabled
Values:
disable(0),
enable(1)
"
 ::= { ne843PicEntry  41 }

ne843PicEntryPcauxr OBJECT-TYPE
SYNTAX      DisplayString
MAX-ACCESS  read-write
STATUS      current
DESCRIPTION
"PIC Auxiliary Relay
Values:
None,
Enabled
"
 ::= { ne843PicEntry  42 }

ne843PicEntrySlote OBJECT-TYPE
SYNTAX      INTEGER {
disable(0),
enable(1)
}
MAX-ACCESS  read-write
STATUS      current
DESCRIPTION
"Slot Enabled
Values:
disable(0),
enable(1)
"
 ::= { ne843PicEntry  43 }

ne843PicEntrySlotrly OBJECT-TYPE
SYNTAX      DisplayString
MAX-ACCESS  read-write
STATUS      current
DESCRIPTION
"Slot Relay
Values:
None,
Enabled
"
 ::= { ne843PicEntry  44 }

ne843PicEntryDpmode OBJECT-TYPE
SYNTAX      DisplayString
MAX-ACCESS  read-write
STATUS      current
DESCRIPTION
"Display Mode
Values:
SCAN,
STATIC
"
 ::= { ne843PicEntry  45 }

ne843PicEntryPnldes OBJECT-TYPE
SYNTAX      DisplayString
MAX-ACCESS  read-write
STATUS      current
DESCRIPTION
"Panel Description"
 ::= { ne843PicEntry  46 }

ne843PicEntryMdl OBJECT-TYPE
SYNTAX      DisplayString
MAX-ACCESS  read-write
STATUS      current
DESCRIPTION
"Panel Model"
 ::= { ne843PicEntry  47 }

ne843PicEntryPnlsn OBJECT-TYPE
SYNTAX      DisplayString
MAX-ACCESS  read-write
STATUS      current
DESCRIPTION
"Panel Serial Number"
 ::= { ne843PicEntry  48 }

ne843PicEntryPnlcc OBJECT-TYPE
SYNTAX      DisplayString
MAX-ACCESS  read-write
STATUS      current
DESCRIPTION
"Panel Comcode"
 ::= { ne843PicEntry  49 }

ne843PicEntryPnlser OBJECT-TYPE
SYNTAX      DisplayString
MAX-ACCESS  read-write
STATUS      current
DESCRIPTION
"Panel Series"
 ::= { ne843PicEntry  50 }

ne843PicEntryPnlclei OBJECT-TYPE
SYNTAX      DisplayString
MAX-ACCESS  read-write
STATUS      current
DESCRIPTION
"Panel Clei Code"
 ::= { ne843PicEntry  51 }

ne843PicEntryCustpn1 OBJECT-TYPE
SYNTAX      DisplayString
MAX-ACCESS  read-write
STATUS      current
DESCRIPTION
"Panel Customer Part Number"
 ::= { ne843PicEntry  52 }

ne843PicEntryAsstag1 OBJECT-TYPE
SYNTAX      DisplayString
MAX-ACCESS  read-write
STATUS      current
DESCRIPTION
"Panel Customer Asset Tag"
 ::= { ne843PicEntry  53 }

ne843PicEntryRtng OBJECT-TYPE
SYNTAX      DisplayString
MAX-ACCESS  read-write
STATUS      current
DESCRIPTION
"Panel Rating"
 ::= { ne843PicEntry  54 }

ne843PicEntryPnlsize OBJECT-TYPE
SYNTAX      DisplayString
MAX-ACCESS  read-write
STATUS      current
DESCRIPTION
"Panel Size"
 ::= { ne843PicEntry  55 }



--
-- table PCM
--

ne843PcmTable    OBJECT-TYPE
SYNTAX SEQUENCE OF Ne843PcmEntry
MAX-ACCESS not-accessible
STATUS current
DESCRIPTION
        "Table of all PIC Current Monitor data"
 ::= { ne843  46 }

ne843PcmEntry OBJECT-TYPE
SYNTAX     Ne843PcmEntry
MAX-ACCESS  not-accessible
STATUS      current
DESCRIPTION
       "Entry of information for one PIC Current Monitor"
INDEX { ne843PcmEntryIndex }
 ::= { ne843PcmTable  1 }

Ne843PcmEntry ::= SEQUENCE {
ne843PcmEntryIndex   INTEGER,
ne843PcmEntryIde   DisplayString,
ne843PcmEntryDes   DisplayString,
ne843PcmEntryVal   DisplayString,
ne843PcmEntrySht   DisplayString,
ne843PcmEntrySha   Integer32,
ne843PcmEntryShv   Integer32
}

ne843PcmEntryIndex OBJECT-TYPE
SYNTAX      INTEGER (0..2147483647)
MAX-ACCESS  read-only
STATUS      current
DESCRIPTION
"Table Index"
 ::= { ne843PcmEntry  1 }

ne843PcmEntryIde OBJECT-TYPE
SYNTAX      DisplayString
MAX-ACCESS  read-only
STATUS      current
DESCRIPTION
"Identifier"
 ::= { ne843PcmEntry  2 }

ne843PcmEntryDes OBJECT-TYPE
SYNTAX      DisplayString
MAX-ACCESS  read-write
STATUS      current
DESCRIPTION
"Description"
 ::= { ne843PcmEntry  3 }

ne843PcmEntryVal OBJECT-TYPE
SYNTAX      DisplayString
MAX-ACCESS  read-only
STATUS      current
DESCRIPTION
"Value"
 ::= { ne843PcmEntry  4 }

ne843PcmEntrySht OBJECT-TYPE
SYNTAX      DisplayString
MAX-ACCESS  read-write
STATUS      current
DESCRIPTION
"Shunt Type
Values:
LOAD,
BATTERY,
NONE
"
 ::= { ne843PcmEntry  5 }

ne843PcmEntrySha OBJECT-TYPE
SYNTAX      Integer32
MAX-ACCESS  read-write
STATUS      current
DESCRIPTION
"Shunt Current"
 ::= { ne843PcmEntry  6 }

ne843PcmEntryShv OBJECT-TYPE
SYNTAX      Integer32(1..150)
MAX-ACCESS  read-write
STATUS      current
DESCRIPTION
"Shunt Voltage"
 ::= { ne843PcmEntry  7 }



--
-- table PVM
--

ne843PvmTable    OBJECT-TYPE
SYNTAX SEQUENCE OF Ne843PvmEntry
MAX-ACCESS not-accessible
STATUS current
DESCRIPTION
        "Table of all PIC Voltage Monitor data"
 ::= { ne843  47 }

ne843PvmEntry OBJECT-TYPE
SYNTAX     Ne843PvmEntry
MAX-ACCESS  not-accessible
STATUS      current
DESCRIPTION
       "Entry of information for one PIC Voltage Monitor"
INDEX { ne843PvmEntryIndex }
 ::= { ne843PvmTable  1 }

Ne843PvmEntry ::= SEQUENCE {
ne843PvmEntryIndex   INTEGER,
ne843PvmEntryIde   DisplayString,
ne843PvmEntryDes   DisplayString,
ne843PvmEntryVal   Integer32
}

ne843PvmEntryIndex OBJECT-TYPE
SYNTAX      INTEGER (0..2147483647)
MAX-ACCESS  read-only
STATUS      current
DESCRIPTION
"Table Index"
 ::= { ne843PvmEntry  1 }

ne843PvmEntryIde OBJECT-TYPE
SYNTAX      DisplayString
MAX-ACCESS  read-only
STATUS      current
DESCRIPTION
"Identifier"
 ::= { ne843PvmEntry  2 }

ne843PvmEntryDes OBJECT-TYPE
SYNTAX      DisplayString
MAX-ACCESS  read-write
STATUS      current
DESCRIPTION
"Description"
 ::= { ne843PvmEntry  3 }

ne843PvmEntryVal OBJECT-TYPE
SYNTAX      Integer32
MAX-ACCESS  read-only
STATUS      current
DESCRIPTION
"Value"
 ::= { ne843PvmEntry  4 }



--
-- table PTM
--

ne843PtmTable    OBJECT-TYPE
SYNTAX SEQUENCE OF Ne843PtmEntry
MAX-ACCESS not-accessible
STATUS current
DESCRIPTION
        "Table of all PIC Temperature Monitor data"
 ::= { ne843  48 }

ne843PtmEntry OBJECT-TYPE
SYNTAX     Ne843PtmEntry
MAX-ACCESS  not-accessible
STATUS      current
DESCRIPTION
       "Entry of information for one PIC Temperature Monitor"
INDEX { ne843PtmEntryIndex }
 ::= { ne843PtmTable  1 }

Ne843PtmEntry ::= SEQUENCE {
ne843PtmEntryIndex   INTEGER,
ne843PtmEntryIde   DisplayString,
ne843PtmEntryDes   DisplayString,
ne843PtmEntryBamt   Integer32,
ne843PtmEntryNat   Integer32,
ne843PtmEntryHamt   Integer32,
ne843PtmEntryLamt   Integer32,
ne843PtmEntryNtm   Integer32,
ne843PtmEntryHbt   Integer32,
ne843PtmEntryLbt   Integer32,
ne843PtmEntryNbut   Integer32,
ne843PtmEntryHbut   Integer32,
ne843PtmEntryLbut   Integer32
}

ne843PtmEntryIndex OBJECT-TYPE
SYNTAX      INTEGER (0..2147483647)
MAX-ACCESS  read-only
STATUS      current
DESCRIPTION
"Table Index"
 ::= { ne843PtmEntry  1 }

ne843PtmEntryIde OBJECT-TYPE
SYNTAX      DisplayString
MAX-ACCESS  read-only
STATUS      current
DESCRIPTION
"Identifier"
 ::= { ne843PtmEntry  2 }

ne843PtmEntryDes OBJECT-TYPE
SYNTAX      DisplayString
MAX-ACCESS  read-write
STATUS      current
DESCRIPTION
"Description"
 ::= { ne843PtmEntry  3 }

ne843PtmEntryBamt OBJECT-TYPE
SYNTAX      Integer32
MAX-ACCESS  read-only
STATUS      current
DESCRIPTION
"Board Ambient Temperature"
 ::= { ne843PtmEntry  4 }

ne843PtmEntryNat OBJECT-TYPE
SYNTAX      Integer32
MAX-ACCESS  read-only
STATUS      current
DESCRIPTION
"Number of Ambient Temperature Probes"
 ::= { ne843PtmEntry  5 }

ne843PtmEntryHamt OBJECT-TYPE
SYNTAX      Integer32
MAX-ACCESS  read-only
STATUS      current
DESCRIPTION
"Hi Ambient Temperature"
 ::= { ne843PtmEntry  6 }

ne843PtmEntryLamt OBJECT-TYPE
SYNTAX      Integer32
MAX-ACCESS  read-only
STATUS      current
DESCRIPTION
"Low Ambient Temperature"
 ::= { ne843PtmEntry  7 }

ne843PtmEntryNtm OBJECT-TYPE
SYNTAX      Integer32
MAX-ACCESS  read-only
STATUS      current
DESCRIPTION
"Number of Battery Temperature Probes"
 ::= { ne843PtmEntry  8 }

ne843PtmEntryHbt OBJECT-TYPE
SYNTAX      Integer32
MAX-ACCESS  read-only
STATUS      current
DESCRIPTION
"Hi Battery Temperature"
 ::= { ne843PtmEntry  9 }

ne843PtmEntryLbt OBJECT-TYPE
SYNTAX      Integer32
MAX-ACCESS  read-only
STATUS      current
DESCRIPTION
"Low Battery Temperature"
 ::= { ne843PtmEntry  10 }

ne843PtmEntryNbut OBJECT-TYPE
SYNTAX      Integer32
MAX-ACCESS  read-only
STATUS      current
DESCRIPTION
"Number of Bus Temperature Probes"
 ::= { ne843PtmEntry  11 }

ne843PtmEntryHbut OBJECT-TYPE
SYNTAX      Integer32
MAX-ACCESS  read-only
STATUS      current
DESCRIPTION
"Hi Bus Temperature"
 ::= { ne843PtmEntry  12 }

ne843PtmEntryLbut OBJECT-TYPE
SYNTAX      Integer32
MAX-ACCESS  read-only
STATUS      current
DESCRIPTION
"Low Bust Temperature"
 ::= { ne843PtmEntry  13 }



--
-- table PCS
--

ne843PcsTable    OBJECT-TYPE
SYNTAX SEQUENCE OF Ne843PcsEntry
MAX-ACCESS not-accessible
STATUS current
DESCRIPTION
        "Table of all PIC Slot data"
 ::= { ne843  49 }

ne843PcsEntry OBJECT-TYPE
SYNTAX     Ne843PcsEntry
MAX-ACCESS  not-accessible
STATUS      current
DESCRIPTION
       "Entry of information for one PIC Slot"
INDEX { ne843PcsEntryIndex }
 ::= { ne843PcsTable  1 }

Ne843PcsEntry ::= SEQUENCE {
ne843PcsEntryIndex   INTEGER,
ne843PcsEntryIde   DisplayString,
ne843PcsEntryDes   DisplayString,
ne843PcsEntryStt   DisplayString,
ne843PcsEntryTyp   DisplayString,
ne843PcsEntryPole   Integer32,
ne843PcsEntryPolp   Integer32,
ne843PcsEntryPopn   DisplayString,
ne843PcsEntryTrp   INTEGER,
ne843PcsEntryBad   INTEGER,
ne843PcsEntryCbf   DisplayString,
ne843PcsEntrySlv   INTEGER,
ne843PcsEntryRtng   Integer32
}

ne843PcsEntryIndex OBJECT-TYPE
SYNTAX      INTEGER (0..2147483647)
MAX-ACCESS  read-only
STATUS      current
DESCRIPTION
"Table Index"
 ::= { ne843PcsEntry  1 }

ne843PcsEntryIde OBJECT-TYPE
SYNTAX      DisplayString
MAX-ACCESS  read-only
STATUS      current
DESCRIPTION
"Identifier"
 ::= { ne843PcsEntry  2 }

ne843PcsEntryDes OBJECT-TYPE
SYNTAX      DisplayString
MAX-ACCESS  read-write
STATUS      current
DESCRIPTION
"Description"
 ::= { ne843PcsEntry  3 }

ne843PcsEntryStt OBJECT-TYPE
SYNTAX      DisplayString
MAX-ACCESS  read-only
STATUS      current
DESCRIPTION
"Status"
 ::= { ne843PcsEntry  4 }

ne843PcsEntryTyp OBJECT-TYPE
SYNTAX      DisplayString
MAX-ACCESS  read-write
STATUS      current
DESCRIPTION
"Type
Values:
Load,
Batt,
picType
"
 ::= { ne843PcsEntry  5 }

ne843PcsEntryPole OBJECT-TYPE
SYNTAX      Integer32
MAX-ACCESS  read-write
STATUS      current
DESCRIPTION
"Number of Poles"
 ::= { ne843PcsEntry  6 }

ne843PcsEntryPolp OBJECT-TYPE
SYNTAX      Integer32
MAX-ACCESS  read-write
STATUS      current
DESCRIPTION
"Slot Pole Position"
 ::= { ne843PcsEntry  7 }

ne843PcsEntryPopn OBJECT-TYPE
SYNTAX      DisplayString
MAX-ACCESS  read-write
STATUS      current
DESCRIPTION
"Slot Pole Open/Closed
Values:
Open,
Closed
"
 ::= { ne843PcsEntry  8 }

ne843PcsEntryTrp OBJECT-TYPE
SYNTAX      INTEGER {
off(0),
on(1)
}
MAX-ACCESS  read-write
STATUS      current
DESCRIPTION
"Slot Tripped
Values:
off(0),
on(1)
"
 ::= { ne843PcsEntry  9 }

ne843PcsEntryBad OBJECT-TYPE
SYNTAX      INTEGER {
off(0),
on(1)
}
MAX-ACCESS  read-write
STATUS      current
DESCRIPTION
"Slot Bad
Values:
off(0),
on(1)
"
 ::= { ne843PcsEntry  10 }

ne843PcsEntryCbf OBJECT-TYPE
SYNTAX      DisplayString
MAX-ACCESS  read-write
STATUS      current
DESCRIPTION
"Slot CB or Fuse
Values:
CB,
Fuse
"
 ::= { ne843PcsEntry  11 }

ne843PcsEntrySlv OBJECT-TYPE
SYNTAX      INTEGER {
off(0),
on(1)
}
MAX-ACCESS  read-write
STATUS      current
DESCRIPTION
"Slot Slave
Values:
off(0),
on(1)
"
 ::= { ne843PcsEntry  12 }

ne843PcsEntryRtng OBJECT-TYPE
SYNTAX      Integer32
MAX-ACCESS  read-write
STATUS      current
DESCRIPTION
"Slot Rtng"
 ::= { ne843PcsEntry  13 }



--
-- table DBY
--

ne843DbyTable    OBJECT-TYPE
SYNTAX SEQUENCE OF Ne843DbyEntry
MAX-ACCESS not-accessible
STATUS current
DESCRIPTION
        "Table of all Distribution Bay data"
 ::= { ne843  50 }

ne843DbyEntry OBJECT-TYPE
SYNTAX     Ne843DbyEntry
MAX-ACCESS  not-accessible
STATUS      current
DESCRIPTION
       "Entry of information for one Distribution Bay"
INDEX { ne843DbyEntryIndex }
 ::= { ne843DbyTable  1 }

Ne843DbyEntry ::= SEQUENCE {
ne843DbyEntryIndex   INTEGER,
ne843DbyEntryIde   DisplayString,
ne843DbyEntryDes   DisplayString,
ne843DbyEntrySn   DisplayString,
ne843DbyEntryStt   DisplayString,
ne843DbyEntrySha   Integer32,
ne843DbyEntryNpl   Integer32,
ne843DbyEntryPmt   DisplayString,
ne843DbyEntryIds   DisplayString,
ne843DbyEntryBze   INTEGER,
ne843DbyEntryOle   INTEGER,
ne843DbyEntryOri   DisplayString,
ne843DbyEntryCmb   INTEGER,
ne843DbyEntrySmw   DisplayString,
ne843DbyEntryCca   DisplayString
}

ne843DbyEntryIndex OBJECT-TYPE
SYNTAX      INTEGER (0..2147483647)
MAX-ACCESS  read-only
STATUS      current
DESCRIPTION
"Table Index"
 ::= { ne843DbyEntry  1 }

ne843DbyEntryIde OBJECT-TYPE
SYNTAX      DisplayString
MAX-ACCESS  read-only
STATUS      current
DESCRIPTION
"Identifier"
 ::= { ne843DbyEntry  2 }

ne843DbyEntryDes OBJECT-TYPE
SYNTAX      DisplayString
MAX-ACCESS  read-write
STATUS      current
DESCRIPTION
"Description"
 ::= { ne843DbyEntry  3 }

ne843DbyEntrySn OBJECT-TYPE
SYNTAX      DisplayString
MAX-ACCESS  read-only
STATUS      current
DESCRIPTION
"Serial Number"
 ::= { ne843DbyEntry  4 }

ne843DbyEntryStt OBJECT-TYPE
SYNTAX      DisplayString
MAX-ACCESS  read-only
STATUS      current
DESCRIPTION
"State"
 ::= { ne843DbyEntry  5 }

ne843DbyEntrySha OBJECT-TYPE
SYNTAX      Integer32(0..4000)
UNITS       "Amps"
MAX-ACCESS  read-write
STATUS      current
DESCRIPTION
"Shunt Rating (Amps)"
 ::= { ne843DbyEntry  6 }

ne843DbyEntryNpl OBJECT-TYPE
SYNTAX      Integer32(1..8)
MAX-ACCESS  read-write
STATUS      current
DESCRIPTION
"Number of Panels"
 ::= { ne843DbyEntry  7 }

ne843DbyEntryPmt OBJECT-TYPE
SYNTAX      DisplayString
MAX-ACCESS  read-write
STATUS      current
DESCRIPTION
"Measurement Type"
 ::= { ne843DbyEntry  8 }

ne843DbyEntryIds OBJECT-TYPE
SYNTAX      DisplayString
MAX-ACCESS  read-write
STATUS      current
DESCRIPTION
"Identification Style"
 ::= { ne843DbyEntry  9 }

ne843DbyEntryBze OBJECT-TYPE
SYNTAX      INTEGER {
disable(0),
enable(1)
}
MAX-ACCESS  read-write
STATUS      current
DESCRIPTION
"Buzzer Enable
Values:
disable(0),
enable(1)
"
 ::= { ne843DbyEntry  10 }

ne843DbyEntryOle OBJECT-TYPE
SYNTAX      INTEGER {
disable(0),
enable(1)
}
MAX-ACCESS  read-write
STATUS      current
DESCRIPTION
"Overload Latch Enable
Values:
disable(0),
enable(1)
"
 ::= { ne843DbyEntry  11 }

ne843DbyEntryOri OBJECT-TYPE
SYNTAX      DisplayString
MAX-ACCESS  read-write
STATUS      current
DESCRIPTION
"Panel Orientation"
 ::= { ne843DbyEntry  12 }

ne843DbyEntryCmb OBJECT-TYPE
SYNTAX      INTEGER {
disable(0),
enable(1)
}
MAX-ACCESS  read-write
STATUS      current
DESCRIPTION
"Combine Panels
Values:
disable(0),
enable(1)
"
 ::= { ne843DbyEntry  13 }

ne843DbyEntrySmw OBJECT-TYPE
SYNTAX      DisplayString
MAX-ACCESS  read-only
STATUS      current
DESCRIPTION
"Shunt Miswired"
 ::= { ne843DbyEntry  14 }

ne843DbyEntryCca OBJECT-TYPE
SYNTAX      DisplayString
MAX-ACCESS  read-only
STATUS      current
DESCRIPTION
"Circuit Assignment"
 ::= { ne843DbyEntry  15 }



--
-- table DPN
--

ne843DpnTable    OBJECT-TYPE
SYNTAX SEQUENCE OF Ne843DpnEntry
MAX-ACCESS not-accessible
STATUS current
DESCRIPTION
        "Table of all Distribution Panel data"
 ::= { ne843  51 }

ne843DpnEntry OBJECT-TYPE
SYNTAX     Ne843DpnEntry
MAX-ACCESS  not-accessible
STATUS      current
DESCRIPTION
       "Entry of information for one Distribution Panel"
INDEX { ne843DpnEntryIndex }
 ::= { ne843DpnTable  1 }

Ne843DpnEntry ::= SEQUENCE {
ne843DpnEntryIndex   INTEGER,
ne843DpnEntryIde   DisplayString,
ne843DpnEntryDes   DisplayString,
ne843DpnEntryAdc   Integer32,
ne843DpnEntryVdc   Integer32,
ne843DpnEntryStt   DisplayString,
ne843DpnEntryPid   Integer32,
ne843DpnEntryEna   INTEGER,
ne843DpnEntryOld   Integer32,
ne843DpnEntryOlt   Integer32,
ne843DpnEntryOlr   INTEGER,
ne843DpnEntryPlt   Integer32,
ne843DpnEntryCct   Integer32,
ne843DpnEntryVlv   DisplayString,
ne843DpnEntryOvl   DisplayString,
ne843DpnEntryFaja   DisplayString,
ne843DpnEntryFajb   DisplayString
}

ne843DpnEntryIndex OBJECT-TYPE
SYNTAX      INTEGER (0..2147483647)
MAX-ACCESS  read-only
STATUS      current
DESCRIPTION
"Table Index"
 ::= { ne843DpnEntry  1 }

ne843DpnEntryIde OBJECT-TYPE
SYNTAX      DisplayString
MAX-ACCESS  read-only
STATUS      current
DESCRIPTION
"Identifier"
 ::= { ne843DpnEntry  2 }

ne843DpnEntryDes OBJECT-TYPE
SYNTAX      DisplayString
MAX-ACCESS  read-write
STATUS      current
DESCRIPTION
"Description"
 ::= { ne843DpnEntry  3 }

ne843DpnEntryAdc OBJECT-TYPE
SYNTAX      Integer32
UNITS       "Amps"
MAX-ACCESS  read-only
STATUS      current
DESCRIPTION
"Current (Amps)"
 ::= { ne843DpnEntry  4 }

ne843DpnEntryVdc OBJECT-TYPE
SYNTAX      Integer32
UNITS       "mV"
MAX-ACCESS  read-only
STATUS      current
DESCRIPTION
"Voltage (mV)"
 ::= { ne843DpnEntry  5 }

ne843DpnEntryStt OBJECT-TYPE
SYNTAX      DisplayString
MAX-ACCESS  read-only
STATUS      current
DESCRIPTION
"State"
 ::= { ne843DpnEntry  6 }

ne843DpnEntryPid OBJECT-TYPE
SYNTAX      Integer32(1..8)
MAX-ACCESS  read-only
STATUS      current
DESCRIPTION
"Panel ID"
 ::= { ne843DpnEntry  7 }

ne843DpnEntryEna OBJECT-TYPE
SYNTAX      INTEGER {
disable(0),
enable(1)
}
MAX-ACCESS  read-write
STATUS      current
DESCRIPTION
"Enable
Values:
disable(0),
enable(1)
"
 ::= { ne843DpnEntry  8 }

ne843DpnEntryOld OBJECT-TYPE
SYNTAX      Integer32(0..300)
UNITS       "Seconds"
MAX-ACCESS  read-write
STATUS      current
DESCRIPTION
"Overload Delay (Seconds)"
 ::= { ne843DpnEntry  9 }

ne843DpnEntryOlt OBJECT-TYPE
SYNTAX      Integer32(0..4000)
UNITS       "amps"
MAX-ACCESS  read-write
STATUS      current
DESCRIPTION
"Overload Threshold (amps)"
 ::= { ne843DpnEntry  10 }

ne843DpnEntryOlr OBJECT-TYPE
SYNTAX      INTEGER {
disable(0),
enable(1)
}
MAX-ACCESS  read-write
STATUS      current
DESCRIPTION
"Redundant Overload
Values:
disable(0),
enable(1)
"
 ::= { ne843DpnEntry  11 }

ne843DpnEntryPlt OBJECT-TYPE
SYNTAX      Integer32(40000..60000)
UNITS       "mV"
MAX-ACCESS  read-write
STATUS      current
DESCRIPTION
"Power Loss Threshold (mV)"
 ::= { ne843DpnEntry  12 }

ne843DpnEntryCct OBJECT-TYPE
SYNTAX      Integer32(1..8)
MAX-ACCESS  read-write
STATUS      current
DESCRIPTION
"Input Circuit"
 ::= { ne843DpnEntry  13 }

ne843DpnEntryVlv OBJECT-TYPE
SYNTAX      DisplayString
MAX-ACCESS  read-only
STATUS      current
DESCRIPTION
"Power Loss"
 ::= { ne843DpnEntry  14 }

ne843DpnEntryOvl OBJECT-TYPE
SYNTAX      DisplayString
MAX-ACCESS  read-only
STATUS      current
DESCRIPTION
"Overload"
 ::= { ne843DpnEntry  15 }

ne843DpnEntryFaja OBJECT-TYPE
SYNTAX      DisplayString
MAX-ACCESS  read-only
STATUS      current
DESCRIPTION
"Distribution Fuse A"
 ::= { ne843DpnEntry  16 }

ne843DpnEntryFajb OBJECT-TYPE
SYNTAX      DisplayString
MAX-ACCESS  read-only
STATUS      current
DESCRIPTION
"Distribution Fuse B"
 ::= { ne843DpnEntry  17 }



END
