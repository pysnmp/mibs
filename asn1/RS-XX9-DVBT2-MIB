--
-- RS-XX9-DVBT2-MIB.mi2
-- MIB generated by MG-SOFT Visual MIB Builder 2010 Version 8.0  Build 403
-- Tuesday, September 08, 2015 at 13:51:54
--

-- *****************************************************************************
-- *****************************************************************************
-- **
-- **  COPYRIGHT      (c) 2011 Rohde & Schwarz GmbH & Co. KG
-- **                          Muehldorfstrasse 15
-- **    R & S                 D-81671 Muenchen
-- **
-- *****************************************************************************
-- **
-- **  MODULE         RS-XX9-DVBT2-MIB
-- **  
-- *****************************************************************************
-- *****************************************************************************

    RS-XX9-DVBT2-MIB DEFINITIONS ::= BEGIN
 
        IMPORTS
            commonNotificationAlarmClass            
                FROM RS-XX9-COMMON-MIB            
            rsXx9DvbT2, rsXx9MibModule            
                FROM RS-XX9-SMI-MIB            
            NotificationMask, NotificationPriority, NotificationState, IndexTransmitter, IndexAB, 
            SwitchOnOff            
                FROM RS-XX9-TC-MIB            
            SnmpAdminString            
                FROM SNMP-FRAMEWORK-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI            
            TruthValue, TEXTUAL-CONVENTION            
                FROM SNMPv2-TC;
    
    
        rsXx9Dvbt2MibModule MODULE-IDENTITY 
            LAST-UPDATED "201508251100Z"		-- August 25, 2015 at 11:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines DVB-T2 specific objects
                of XX9000 transmitting systems from Rohde & Schwarz.
                
                The following MIBs are related to this:
                - RS-COMMON-MIB         - mandatory for this MIB.
                - RS-XX9-SMI-MIB        - mandatory for this MIB.
                - RS-XX9-TC-MIB         - mandatory for this MIB.
                - RS-XX9-COMMON-MIB     - mandatory for this MIB."
            REVISION "201508251100Z"		-- August 25, 2015 at 11:00 GMT
            DESCRIPTION 
                "obsoleted dvbt2T2MiTimeInterleaverBuffer
                added notifications dvbt2CompositeSummary, dvbt2CompositeProfiles, dvbt2CompositeFrameLength, dvbt2SubIaState, dvbt2SubConfigurationValid, dvbt2SubConfigurationSupported, dvbt2SubConfigurationMatched
                added composite(3) for multiProfile to dvbt2ConfigurationT2MiInterface
                added dvbt2CoderSub tree
                "
            REVISION "201412221600Z"		-- December 22, 2014 at 16:00 GMT
            DESCRIPTION 
                "updated description texts
                "
            REVISION "201412031100Z"		-- December 03, 2014 at 11:00 GMT
            DESCRIPTION 
                "added dvbt2T2MiTimeInterleaverBuffer"
            REVISION "201411031600Z"		-- November 03, 2014 at 16:00 GMT
            DESCRIPTION 
                "obsoleted dvbt2OutPlpFecBlocks, dvbt2OutPlpISSY
                "
            REVISION "201405151500Z"		-- May 15, 2014 at 15:00 GMT
            DESCRIPTION 
                "added dvbt2StDejitterBufDelay, dvbt2StResidualDelay
                added dvbt2StConfigurationMsg"
            REVISION "201401141700Z"		-- January 14, 2014 at 17:00 GMT
            DESCRIPTION 
                "added T2ConfigAdaption
                added TsMiDejitterBufDelay
                unobsoleted dvbt2LocalizationPaprTrSource and dvbt2OutLocalizationPaprTrSource"
            REVISION "201109121200Z"		-- September 12, 2011 at 12:00 GMT
            DESCRIPTION 
                "Preliminary version."
            ::= { rsXx9MibModule 5 }

        
    
--
-- Textual conventions
--
    
        Dvbt2IndividualAddressingSource ::= TEXTUAL-CONVENTION
            STATUS current
            DESCRIPTION 
                "dataNotAnnounced(1) - individual addressing information not available
                viaBroadcast(2)     - all transmitters of the network got the same
                                      information via broadcast
                txSpecific(3)       - a special information was given for this TX identifier"
            SYNTAX INTEGER
                {
                dataNotAnnounced(1),
                viaBroadcast(2),
                txSpecific(3)
                }

        Dvbt2ChannelBandwidth ::= TEXTUAL-CONVENTION
            STATUS current
            DESCRIPTION 
                "mhz1p7(3) -  1.7 MHz
                mhz5(4)   -  5 MHz
                mhz6(5)   -  6 MHz
                mhz7(6)   -  7 MHz
                mhz8(7)   -  8 MHz"
            SYNTAX INTEGER
                {
                mhz1p7(3),
                mhz5(4),
                mhz6(5),
                mhz7(6),
                mhz8(7)
                }

        Dvbt2PlpType ::= TEXTUAL-CONVENTION
            STATUS current
            DESCRIPTION 
                "PLP type."
            SYNTAX INTEGER
                {
                common(3),
                dataType1(4),
                dataType2(5)
                }

        Dvbt2Modulation ::= TEXTUAL-CONVENTION
            STATUS current
            DESCRIPTION 
                "PLP modulation."
            SYNTAX INTEGER
                {
                qpsk(3),
                qam16(4),
                qam64(5),
                qam256(6)
                }

        Dvbt2CodeRate ::= TEXTUAL-CONVENTION
            STATUS current
            DESCRIPTION 
                "PLP code rate."
            SYNTAX INTEGER
                {
                oneHalf(3),
                threeFifth(4),
                twoThird(5),
                threeFourth(6),
                fourFifth(7),
                fiveSixth(8),
                oneThird(9),
                twoFifth(10)
                }

        Dvbt2FEC ::= TEXTUAL-CONVENTION
            STATUS current
            DESCRIPTION 
                "PLP FEC type."
            SYNTAX INTEGER
                {
                ldpc16K(3),
                ldpc64K(4)
                }

        Dvbt2TimeInterleaverType ::= TEXTUAL-CONVENTION
            STATUS current
            DESCRIPTION 
                "Type of time-interleaving."
            SYNTAX INTEGER
                {
                single(3),
                multi(4)
                }

        Dvbt2BasebandMode ::= TEXTUAL-CONVENTION
            STATUS current
            DESCRIPTION 
                "highEfficiency(4) - certain normally unused bytes in the data stream
                are used for data transmission.
                This mode may not be supported by some devices."
            SYNTAX INTEGER
                {
                normal(3),
                highEfficiency(4)
                }

        Dvbt2Layer1Modulation ::= TEXTUAL-CONVENTION
            STATUS current
            DESCRIPTION 
                "Constellation of the layer 1 post signalling data block."
            SYNTAX INTEGER
                {
                bpsk(3),
                qpsk(4),
                qam16(5),
                qam64(6)
                }

        Dvbt2Layer1FEC ::= TEXTUAL-CONVENTION
            STATUS current
            DESCRIPTION 
                "Layer 1 FEC used for the layer 1 post signalling data block."
            SYNTAX INTEGER { ldpc16(3) }

        Dvbt2Layer1CodeRate ::= TEXTUAL-CONVENTION
            STATUS current
            DESCRIPTION 
                "Coding of the layer 1 post signalling data block."
            SYNTAX INTEGER { oneHalf(3) }

        Dvbt2TransmissionSystem ::= TEXTUAL-CONVENTION
            STATUS current
            DESCRIPTION 
                "t2Miso(2) is an approach to improve the link throughput using
                two antennas on transmitter site while using a single receiver antenna."
            SYNTAX INTEGER
                {
                t2SISO(3),
                t2MISO(4),
                nonT2(5),
                t2SISOlite(6),
                t2MISOlite(7)
                }

        Dvbt2FftSize ::= TEXTUAL-CONVENTION
            STATUS current
            DESCRIPTION 
                "FFT size."
            SYNTAX INTEGER
                {
                k1(2),
                k2(3),
                k4(4),
                k8(5),
                k16(6),
                k32(7)
                }

        Dvbt2GuardInterval ::= TEXTUAL-CONVENTION
            STATUS current
            DESCRIPTION 
                "Guard interval of the super-frame.
                oneDiv32(2)       -> 1/32
                oneDiv16(3)       -> 1/16
                oneDiv8(4)        -> 1/8
                oneDiv4(5)        -> 1/4
                oneDiv128(6)      -> 1/128
                nineteenDiv128(7) -> 19/128
                nineteenDiv256(8) -> 19/256"
            SYNTAX INTEGER
                {
                oneDiv32(2),
                oneDiv16(3),
                oneDiv8(4),
                oneDiv4(5),
                oneDiv128(6),
                nineteenDiv128(7),
                nineteenDiv256(8)
                }

        Dvbt2PilotPattern ::= TEXTUAL-CONVENTION
            STATUS current
            DESCRIPTION 
                "The scattered pilot pattern used for the data OFDM symbols."
            SYNTAX INTEGER
                {
                pp1(3),
                pp2(4),
                pp3(5),
                pp4(6),
                pp5(7),
                pp6(8),
                pp7(9),
                pp8(10)
                }

        Dvbt2PaprReduction ::= TEXTUAL-CONVENTION
            STATUS current
            DESCRIPTION 
                "PAPR (Peak to Average Power Ratio) reduction used, if any.
                ace(4)   - Active Constellation Extension
                tr(5)    - Tone Reservation
                aceTr(6) - ACE and TR combined"
            SYNTAX INTEGER
                {
                none(3),
                ace(4),
                tr(5),
                aceTr(6)
                }

        Dvbt2CellIdSource ::= TEXTUAL-CONVENTION
            STATUS current
            DESCRIPTION 
                "The Cell ID enables the receiver to identify a DVB-T2 cell.
                manual(1) - from dvbt2LocalizationCellIdManual
                l1(2)     - from the L1 frame information
                            of the DVB-T2 gateway stream
                ia(3)     - from the individual addressing data
                            of the DVB-T2 gateway stream"
            SYNTAX INTEGER
                {
                manual(1),
                l1(2),
                ia(3)
                }

        Dvbt2L1FrequencySource ::= TEXTUAL-CONVENTION
            STATUS current
            DESCRIPTION 
                "Source of L1 frequency shift.
                If a T2-MI interface is used, you usually select l1(2),
                but for testing manual(1) may be selected.
                If TS feed is used, only manual(1) is possible."
            SYNTAX INTEGER
                {
                manual(1),
                l1(2)
                }

        Dvbt2TxDelayOffsetSource ::= TEXTUAL-CONVENTION
            STATUS current
            DESCRIPTION 
                "Source for transmitter specific transmitting delay.
                If a T2-MI interface is used, you may choose:
                ia(2)  - take from IA parameters
                off(1) - deactivated
                If TS feed is used, no choice is possible."
            SYNTAX INTEGER
                {
                off(1),
                ia(2)
                }

        Dvbt2T2Version ::= TEXTUAL-CONVENTION
            STATUS current
            DESCRIPTION 
                "v111(3) - version 1.1.1
                v121(4) - version 1.2.1
                v131(5) - version 1.3.1"
            SYNTAX INTEGER
                {
                v111(3),
                v121(4),
                v131(5)
                }

        Dvbt2OnOff ::= TEXTUAL-CONVENTION
            STATUS current
            DESCRIPTION 
                "On / Off information for certain DVB-T2 values."
            SYNTAX INTEGER
                {
                undefined(1),
                off(3),
                on(4)
                }

    
--
-- Node definitions
--
    
        rsXx9Dvbt2Notifications OBJECT IDENTIFIER ::= { rsXx9DvbT2 0 }

        
        dvbt2L1State NOTIFICATION-TYPE
            OBJECTS { commonNotificationAlarmClass, dvbt2StatusNotificationPriority, dvbt2StatusNotificationState }
            STATUS current
            DESCRIPTION 
                "When using a T2 MI interface this status shows,
                how the values from the L1 frame information are used:
                
                Possible values:
                undefined(1) 
                off(2)       - L1 frame information values not used
                fault(3)     - L1 framing is not supported by this software version,
                               please update the TCE software
                ok(5)        - L1 frame information values are correct
                               and are used for modulation
                
                Notification class: warning"
            ::= { rsXx9Dvbt2Notifications 1 }

        
        dvbt2IaState NOTIFICATION-TYPE
            OBJECTS { commonNotificationAlarmClass, dvbt2StatusNotificationPriority, dvbt2StatusNotificationState }
            STATUS current
            DESCRIPTION 
                "Shows usage of the 'individual addressing' parameters
                of the data stream.
                
                Possible values:
                undefined(1)
                off(2)       - not used
                warning(4)   - in use, but not available
                ok(5)        - in use and available
                
                Notification class: warning"
            ::= { rsXx9Dvbt2Notifications 2 }

        
        dvbt2ConfigurationValid NOTIFICATION-TYPE
            OBJECTS { commonNotificationAlarmClass, dvbt2StatusNotificationPriority, dvbt2StatusNotificationState }
            STATUS current
            DESCRIPTION 
                "Shows whether the configuration of DVB-T2 parameters is coherent.
                
                Possible values:
                off(2)     - unchecked
                warning(4) - invalid configuration
                ok(5)      - valid configuration
                
                Notification class: warning"
            ::= { rsXx9Dvbt2Notifications 5 }

        
        dvbt2ConfigurationSupported NOTIFICATION-TYPE
            OBJECTS { commonNotificationAlarmClass, dvbt2StatusNotificationPriority, dvbt2StatusNotificationState }
            STATUS current
            DESCRIPTION 
                "Indicates whether the selected modualtion mode is 
                supported by this exciter.
                
                Possible values:
                off(2)     - unchecked
                warning(4) - unsupported configuration
                ok(5)      - supported configuration
                
                Notification class: warning"
            ::= { rsXx9Dvbt2Notifications 6 }

        
        dvbt2ConfigurationMatched NOTIFICATION-TYPE
            OBJECTS { commonNotificationAlarmClass, dvbt2StatusNotificationPriority, dvbt2StatusNotificationState }
            STATUS current
            DESCRIPTION 
                "Indicates whether the configuration of the channel 
                bandwidth is consistent. If not, an error message is output.
                
                Possible values:
                off(2)     -
                warning(4) - invalid configuration
                ok(5)      - valid configuration
                
                Notification class: warning"
            ::= { rsXx9Dvbt2Notifications 7 }

        
        dvbt2EncoderSummary NOTIFICATION-TYPE
            OBJECTS { commonNotificationAlarmClass, dvbt2StatusNotificationPriority, dvbt2StatusNotificationState }
            STATUS current
            DESCRIPTION 
                "Encoder summary state.
                
                Possible values:
                off(2)
                warning(4)
                ok(5)
                
                Notification class: warning"
            ::= { rsXx9Dvbt2Notifications 8 }

        
        dvbt2Test NOTIFICATION-TYPE
            OBJECTS { commonNotificationAlarmClass, dvbt2StatusNotificationPriority, dvbt2StatusNotificationState }
            STATUS current
            DESCRIPTION 
                "Possible values:
                off(2)     - no test signal generation
                warning(4) - test signal generation is activated
                
                Notification class: warning"
            ::= { rsXx9Dvbt2Notifications 9 }

        
        dvbt2SupportedPlps NOTIFICATION-TYPE
            OBJECTS { commonNotificationAlarmClass, dvbt2StatusNotificationPriority, dvbt2StatusNotificationState }
            STATUS current
            DESCRIPTION 
                "
                Possible values:
                off(2)
                warning(4)
                ok(5)
                
                Notification class: warning"
            ::= { rsXx9Dvbt2Notifications 10 }

        
        dvbt2SupportedTrIterations NOTIFICATION-TYPE
            OBJECTS { commonNotificationAlarmClass, dvbt2StatusNotificationPriority, dvbt2StatusNotificationState }
            STATUS current
            DESCRIPTION 
                "
                Possible values:
                off(2)
                warning(4)
                ok(5)
                
                Notification class: warning"
            ::= { rsXx9Dvbt2Notifications 11 }

        
        dvbt2T2MiTimeInterleaverBuffer NOTIFICATION-TYPE
            OBJECTS { commonNotificationAlarmClass, dvbt2StatusNotificationPriority, dvbt2StatusNotificationState }
            STATUS obsolete
            DESCRIPTION 
                "obsolete
                
                Possible values:
                undefined(1)
                off(2)       - not used
                warning(4)   - underflow
                ok(5)        - ok
                "
            ::= { rsXx9Dvbt2Notifications 12 }

        
        dvbt2CompositeSummary NOTIFICATION-TYPE
            OBJECTS { commonNotificationAlarmClass, dvbt2StatusNotificationPriority, dvbt2StatusNotificationState }
            STATUS current
            DESCRIPTION 
                "Description.
                
                Possible values:
                off(2)       - 
                warning(4)   - 
                ok(5)        - 
                "
            ::= { rsXx9Dvbt2Notifications 100 }

        
        dvbt2CompositeProfiles NOTIFICATION-TYPE
            OBJECTS { commonNotificationAlarmClass, dvbt2StatusNotificationPriority, dvbt2StatusNotificationState }
            STATUS current
            DESCRIPTION 
                "Description.
                
                Possible values:
                off(2)       - 
                warning(4)   - 
                ok(5)        - 
                "
            ::= { rsXx9Dvbt2Notifications 101 }

        
        dvbt2CompositeFrameLength NOTIFICATION-TYPE
            OBJECTS { commonNotificationAlarmClass, dvbt2StatusNotificationPriority, dvbt2StatusNotificationState }
            STATUS current
            DESCRIPTION 
                "Description.
                
                Possible values:
                off(2)       - 
                warning(4)   - 
                ok(5)        - 
                "
            ::= { rsXx9Dvbt2Notifications 102 }

        
        dvbt2SubIaState NOTIFICATION-TYPE
            OBJECTS { commonNotificationAlarmClass, dvbt2StatusNotificationPriority, dvbt2StatusNotificationState }
            STATUS current
            DESCRIPTION 
                "Shows usage of the 'individual addressing' parameters
                of the data stream.
                
                Possible values:
                undefined(1)
                off(2)       - not used
                warning(4)   - in use, but not available
                ok(5)        - in use and available
                
                Notification class: warning"
            ::= { rsXx9Dvbt2Notifications 202 }

        
        dvbt2SubConfigurationValid NOTIFICATION-TYPE
            OBJECTS { commonNotificationAlarmClass, dvbt2StatusNotificationPriority, dvbt2StatusNotificationState }
            STATUS current
            DESCRIPTION 
                "Shows whether the configuration of DVB-T2 parameters is coherent.
                
                Possible values:
                off(2)     - unchecked
                warning(4) - invalid configuration
                ok(5)      - valid configuration
                
                Notification class: warning"
            ::= { rsXx9Dvbt2Notifications 205 }

        
        dvbt2SubConfigurationSupported NOTIFICATION-TYPE
            OBJECTS { commonNotificationAlarmClass, dvbt2StatusNotificationPriority, dvbt2StatusNotificationState }
            STATUS current
            DESCRIPTION 
                "Indicates whether the selected modualtion mode is 
                supported by this exciter.
                
                Possible values:
                off(2)     - unchecked
                warning(4) - unsupported configuration
                ok(5)      - supported configuration
                
                Notification class: warning"
            ::= { rsXx9Dvbt2Notifications 206 }

        
        dvbt2SubConfigurationMatched NOTIFICATION-TYPE
            OBJECTS { commonNotificationAlarmClass, dvbt2StatusNotificationPriority, dvbt2StatusNotificationState }
            STATUS current
            DESCRIPTION 
                "Indicates whether the configuration of the channel 
                bandwidth is consistent. If not, an error message is output.
                
                Possible values:
                off(2)     -
                warning(4) - invalid configuration
                ok(5)      - valid configuration
                
                Notification class: warning"
            ::= { rsXx9Dvbt2Notifications 207 }

        
        rsXx9Dvbt2Objects OBJECT IDENTIFIER ::= { rsXx9DvbT2 1 }

        
        dvbt2Status OBJECT IDENTIFIER ::= { rsXx9Dvbt2Objects 1 }

        
        dvbt2StatusNotificationTable OBJECT-TYPE
            SYNTAX SEQUENCE OF Dvbt2StatusNotificationEntry
            MAX-ACCESS not-accessible
            STATUS current
            DESCRIPTION
                "The context information/configuration for the
                DVB-T2 status notifications."
            ::= { dvbt2Status 1 }

        
        dvbt2StatusNotificationEntry OBJECT-TYPE
            SYNTAX Dvbt2StatusNotificationEntry
            MAX-ACCESS not-accessible
            STATUS current
            DESCRIPTION
                "An entry in the dvbt2StatusNotificationTable."
            INDEX { dvbt2StatusNotificationTxIdx, dvbt2StatusNotificationExcIdx, dvbt2StatusNotificationIdx }
            ::= { dvbt2StatusNotificationTable 1 }

        
        Dvbt2StatusNotificationEntry ::=
            SEQUENCE { 
                dvbt2StatusNotificationTxIdx
                    IndexTransmitter,
                dvbt2StatusNotificationExcIdx
                    IndexAB,
                dvbt2StatusNotificationIdx
                    Unsigned32,
                dvbt2StatusNotificationName
                    INTEGER,
                dvbt2StatusNotificationMask
                    NotificationMask,
                dvbt2StatusNotificationPriority
                    NotificationPriority,
                dvbt2StatusNotificationState
                    NotificationState
             }

        dvbt2StatusNotificationTxIdx OBJECT-TYPE
            SYNTAX IndexTransmitter
            MAX-ACCESS not-accessible
            STATUS current
            DESCRIPTION
                "The transmitter index."
            ::= { dvbt2StatusNotificationEntry 1 }

        
        dvbt2StatusNotificationExcIdx OBJECT-TYPE
            SYNTAX IndexAB
            MAX-ACCESS not-accessible
            STATUS current
            DESCRIPTION
                "This index distinguishes the exiters.
                Necessary if you have dual drive transmitters."
            ::= { dvbt2StatusNotificationEntry 2 }

        
        dvbt2StatusNotificationIdx OBJECT-TYPE
            SYNTAX Unsigned32 (1..12)
            MAX-ACCESS not-accessible
            STATUS current
            DESCRIPTION
                "The notification number as below rsXx9Dvbt2Notifications.
                This is a helper column and therefore not-accessible."
            ::= { dvbt2StatusNotificationEntry 3 }

        
        dvbt2StatusNotificationName OBJECT-TYPE
            SYNTAX INTEGER
                {
                dvbt2L1State(1),
                dvbt2IaState(2),
                dvbt2ConfigurationValid(5),
                dvbt2ConfigurationSupported(6),
                dvbt2ConfigurationMatched(7),
                dvbt2EncoderSummary(8),
                dvbt2Test(9),
                dvbt2SupportedPlps(10),
                dvbt2SupportedTrIterations(11),
                dvbt2T2MiTimeInterleaverBuffer(12),
                dvbt2CompositeSummary(100),
                dvbt2CompositeProfiles(101),
                dvbt2CompositeFrameLength(102),
                dvbt2SubIaState(202),
                dvbt2SubConfigurationValid(205),
                dvbt2SubConfigurationSupported(206),
                dvbt2SubConfigurationMatched(207)
                }
            MAX-ACCESS read-write
            STATUS current
            DESCRIPTION
                "The notification number as an enumeration.
                The enumeration correlates with the notifications under rsXx9Dvbt2Notifications."
            ::= { dvbt2StatusNotificationEntry 4 }

        
        dvbt2StatusNotificationMask OBJECT-TYPE
            SYNTAX NotificationMask
            MAX-ACCESS read-write
            STATUS current
            DESCRIPTION
                "See TextualConvention for details."
            ::= { dvbt2StatusNotificationEntry 5 }

        
        dvbt2StatusNotificationPriority OBJECT-TYPE
            SYNTAX NotificationPriority
            MAX-ACCESS read-write
            STATUS current
            DESCRIPTION
                "See TextualConvention for details."
            ::= { dvbt2StatusNotificationEntry 6 }

        
        dvbt2StatusNotificationState OBJECT-TYPE
            SYNTAX NotificationState
            MAX-ACCESS read-only
            STATUS current
            DESCRIPTION
                "See TextualConvention for details."
            ::= { dvbt2StatusNotificationEntry 7 }

        
        dvbt2StateTable OBJECT-TYPE
            SYNTAX SEQUENCE OF Dvbt2StateEntry
            MAX-ACCESS not-accessible
            STATUS current
            DESCRIPTION
                "DVB-T2 state information."
            ::= { dvbt2Status 2 }

        
        dvbt2StateEntry OBJECT-TYPE
            SYNTAX Dvbt2StateEntry
            MAX-ACCESS not-accessible
            STATUS current
            DESCRIPTION
                "An entry for a specific exciter."
            INDEX { dvbt2StatusNotificationTxIdx, dvbt2StatusNotificationExcIdx }
            ::= { dvbt2StateTable 1 }

        
        Dvbt2StateEntry ::=
            SEQUENCE { 
                dvbt2StInputDetected
                    INTEGER,
                dvbt2StInputMatched
                    INTEGER,
                dvbt2StInputRequired
                    INTEGER,
                dvbt2StConfigAdaptionState
                    INTEGER,
                dvbt2StDejitterBufDelay
                    Integer32,
                dvbt2StResidualDelay
                    Unsigned32,
                dvbt2StConfigurationMsg
                    SnmpAdminString
             }

        dvbt2StInputDetected OBJECT-TYPE
            SYNTAX INTEGER
                {
                off(1),
                unlocked(2),
                internal(3),
                mpeg(4),
                t2mi(5)
                }
            MAX-ACCESS read-only
            STATUS current
            DESCRIPTION
                "The current input state.
                internal(3) represents the test generator.
                unlocked(2), mpeg(4), t2mi(5): the status of the active input."
            ::= { dvbt2StateEntry 1 }

        
        dvbt2StInputMatched OBJECT-TYPE
            SYNTAX INTEGER
                {
                off(2),
                no(4),
                yes(5)
                }
            MAX-ACCESS read-only
            STATUS current
            DESCRIPTION
                "Result of comparison of dvbt2StInputDetected
                and dvbt2StInputRequired."
            ::= { dvbt2StateEntry 2 }

        
        dvbt2StInputRequired OBJECT-TYPE
            SYNTAX INTEGER
                {
                off(1),
                internal(3),
                mpeg(4),
                t2mi(5)
                }
            MAX-ACCESS read-only
            STATUS current
            DESCRIPTION
                "The current required input state.
                off(1) is startup value, only.
                internal(3) is the test generator.
                mpeg(4), t2mi(5): the requirement towards an active input."
            ::= { dvbt2StateEntry 3 }

        
        dvbt2StConfigAdaptionState OBJECT-TYPE
            SYNTAX INTEGER
                {
                undefined(1),
                notUsed(2),
                wrongConfig(4),
                ok(5)
                }
            MAX-ACCESS read-only
            STATUS current
            DESCRIPTION
                "Description."
            ::= { dvbt2StateEntry 4 }

        
        dvbt2StDejitterBufDelay OBJECT-TYPE
            SYNTAX Integer32 (-1000000..1000000)
            UNITS "mus"
            MAX-ACCESS read-only
            STATUS current
            DESCRIPTION
                "This displays the delay of the T2MI stream within the dejitter buffer. 
                The value varies after the transmission has started due to 
                conditions on the input network. This value should be positive. 
                A negative value may impose transmission interrupts."
            ::= { dvbt2StateEntry 5 }

        
        dvbt2StResidualDelay OBJECT-TYPE
            SYNTAX Unsigned32 (0..500000)
            UNITS "mus"
            MAX-ACCESS read-only
            STATUS current
            DESCRIPTION
                "Delay of the signal controlled by the SFN Synchronization 
                to meet the desired transmission time. 
                The value is fix after transmission has started. 
                To achieve a higher robustness against input jitter, 
                this value can be reduced by increasing the dejitter buffer delay.
                "
            ::= { dvbt2StateEntry 6 }

        
        dvbt2StConfigurationMsg OBJECT-TYPE
            SYNTAX SnmpAdminString (SIZE (0..160))
            MAX-ACCESS read-only
            STATUS current
            DESCRIPTION
                "Description."
            ::= { dvbt2StateEntry 7 }

        
        dvbt2Setup OBJECT IDENTIFIER ::= { rsXx9Dvbt2Objects 2 }

        
        dvbt2ConfigurationTable OBJECT-TYPE
            SYNTAX SEQUENCE OF Dvbt2ConfigurationEntry
            MAX-ACCESS not-accessible
            STATUS current
            DESCRIPTION
                "DVB-T2 configuration."
            ::= { dvbt2Setup 1 }

        
        dvbt2ConfigurationEntry OBJECT-TYPE
            SYNTAX Dvbt2ConfigurationEntry
            MAX-ACCESS not-accessible
            STATUS current
            DESCRIPTION
                "An entry in the dvbt2ConfigurationTable."
            INDEX { dvbt2ConfigurationTxIdx, dvbt2ConfigurationExcIdx }
            ::= { dvbt2ConfigurationTable 1 }
-- An entry in the dvbt2ConfigurationTable.
        
        Dvbt2ConfigurationEntry ::=
            SEQUENCE { 
                dvbt2ConfigurationTxIdx
                    IndexTransmitter,
                dvbt2ConfigurationExcIdx
                    IndexAB,
                dvbt2ConfigurationT2MiInterface
                    INTEGER,
                dvbt2ConfigurationT2MiPID
                    Unsigned32,
                dvbt2ConfigurationT2MiSID
                    Unsigned32,
                dvbt2ConfigurationT2ConfigAdaption
                    INTEGER,
                dvbt2ConfigurationT2MiDejitterBufDelay
                    Unsigned32
             }

        dvbt2ConfigurationTxIdx OBJECT-TYPE
            SYNTAX IndexTransmitter
            MAX-ACCESS not-accessible
            STATUS current
            DESCRIPTION
                "The transmitter index."
            ::= { dvbt2ConfigurationEntry 1 }

        
        dvbt2ConfigurationExcIdx OBJECT-TYPE
            SYNTAX IndexAB
            MAX-ACCESS not-accessible
            STATUS current
            DESCRIPTION
                "This index distinguishes the exiters.
                Necessary if you have dual drive transmitters."
            ::= { dvbt2ConfigurationEntry 2 }

        
        dvbt2ConfigurationT2MiInterface OBJECT-TYPE
            SYNTAX INTEGER
                {
                on(1),
                off(2),
                composite(3)
                }
            MAX-ACCESS read-write
            STATUS current
            DESCRIPTION
                "on(1) - Uses the incoming T2-MI stream from a DVB-T2 gateway
                         to configure the Modulator.
                off(2) - Uses the incoming MPEG transport stream directly
                         as payload for single PLP."
            ::= { dvbt2ConfigurationEntry 3 }

        
        dvbt2ConfigurationT2MiPID OBJECT-TYPE
            SYNTAX Unsigned32 (0..8191)
            MAX-ACCESS read-write
            STATUS current
            DESCRIPTION
                "Only if dvbt2ConfigurationT2MiInterface is on(1):
                the packet ID of the T2-MI elementary stream."
            ::= { dvbt2ConfigurationEntry 4 }

        
        dvbt2ConfigurationT2MiSID OBJECT-TYPE
            SYNTAX Unsigned32 (0..7)
            MAX-ACCESS read-write
            STATUS current
            DESCRIPTION
                "Only if dvbt2FsT2Version is at least v131(5):
                "
            ::= { dvbt2ConfigurationEntry 5 }

        
        dvbt2ConfigurationT2ConfigAdaption OBJECT-TYPE
            SYNTAX INTEGER
                {
                none(1),
                staticSinglePLP(2),
                staticMultiPLP(3)
                }
            MAX-ACCESS read-write
            STATUS current
            DESCRIPTION
                "Defines adaptation of the processing to the configuration at the input. 
                
                None: This setting can always be used; it does, however, lead to a 
                high processing delay through the transmitter. 
                Static single PLP: This setting can only be used if the data stream 
                only contains one PLP (Physical Layer Pipe). It decreases the 
                processing delay through the exciter.
                
                staticMultiPLP(3) is not supported anymore.
                "
            ::= { dvbt2ConfigurationEntry 6 }

        
        dvbt2ConfigurationT2MiDejitterBufDelay OBJECT-TYPE
            SYNTAX Unsigned32 (0..1000)
            UNITS "ms"
            MAX-ACCESS read-write
            STATUS current
            DESCRIPTION
                "Description."
            ::= { dvbt2ConfigurationEntry 7 }

        
        dvbt2LocalizationTable OBJECT-TYPE
            SYNTAX SEQUENCE OF Dvbt2LocalizationEntry
            MAX-ACCESS not-accessible
            STATUS current
            DESCRIPTION
                "DVB-T2 localization."
            ::= { dvbt2Setup 2 }

        
        dvbt2LocalizationEntry OBJECT-TYPE
            SYNTAX Dvbt2LocalizationEntry
            MAX-ACCESS not-accessible
            STATUS current
            DESCRIPTION
                "An entry in the dvbt2LocalizationTable."
            AUGMENTS { dvbt2ConfigurationEntry }
            ::= { dvbt2LocalizationTable 1 }

        
        Dvbt2LocalizationEntry ::=
            SEQUENCE { 
                dvbt2LocalizationTxIdentifier
                    Unsigned32,
                dvbt2LocalizationCellIdSource
                    Dvbt2CellIdSource,
                dvbt2LocalizationCellIdManual
                    Unsigned32,
                dvbt2LocalizationMisoGroupSource
                    INTEGER,
                dvbt2LocalizationMisoGroupManual
                    INTEGER,
                dvbt2LocalizationNetworkIdManual
                    Unsigned32,
                dvbt2LocalizationSystemIdManual
                    Unsigned32,
                dvbt2LocalizationL1FrequencySource
                    Dvbt2L1FrequencySource,
                dvbt2LocalizationL1FrequencyManual
                    Unsigned32,
                dvbt2LocalizationTxDelayOffsetSource
                    Dvbt2TxDelayOffsetSource,
                dvbt2LocalizationPaprTrSource
                    INTEGER
             }

        dvbt2LocalizationTxIdentifier OBJECT-TYPE
            SYNTAX Unsigned32 (0..65535)
            MAX-ACCESS read-write
            STATUS current
            DESCRIPTION
                "Used to address a TV transmitter within a DVB-T2 network."
            ::= { dvbt2LocalizationEntry 3 }

        
        dvbt2LocalizationCellIdSource OBJECT-TYPE
            SYNTAX Dvbt2CellIdSource
            MAX-ACCESS read-write
            STATUS current
            DESCRIPTION
                "Source for the cell ID."
            ::= { dvbt2LocalizationEntry 4 }

        
        dvbt2LocalizationCellIdManual OBJECT-TYPE
            SYNTAX Unsigned32 (0..65535)
            MAX-ACCESS read-write
            STATUS current
            DESCRIPTION
                "The cell ID used when dvbt2LocalizationCellIdSource is manual(1).
                The cell ID can be changed without signal interruption."
            ::= { dvbt2LocalizationEntry 5 }

        
        dvbt2LocalizationMisoGroupSource OBJECT-TYPE
            SYNTAX INTEGER
                {
                off(1),
                manual(2),
                ia(3)
                }
            MAX-ACCESS read-write
            STATUS current
            DESCRIPTION
                "The MISO group can be configured either manually directly on the transmitter
                or automatically using the Individual Addressing (IA) data via the DVB_T2 gateway.
                The group can be switched at any time without signal interruption.
                
                manual(2) - from dvbt2LocalizationMisoGroupManual
                ia(3)     - from the individual addressing data
                            of the DVB-T2 gateway stream"
            ::= { dvbt2LocalizationEntry 6 }

        
        dvbt2LocalizationMisoGroupManual OBJECT-TYPE
            SYNTAX INTEGER
                {
                group1(4),
                group2(5)
                }
            MAX-ACCESS read-write
            STATUS current
            DESCRIPTION
                "The MISO group used when dvbt2LocalizationMisoGroupSource is manual(1).
                The MISO group can be changed without signal interruption."
            ::= { dvbt2LocalizationEntry 7 }

        
        dvbt2LocalizationNetworkIdManual OBJECT-TYPE
            SYNTAX Unsigned32 (0..65535)
            MAX-ACCESS read-write
            STATUS current
            DESCRIPTION
                "The network ID uniquely defines the current DVB-T2 network.
                If a T2-MI interface is used, this value is specified
                from the DVB-T2 gateway.
                Otherwise it is defined here."
            ::= { dvbt2LocalizationEntry 8 }

        
        dvbt2LocalizationSystemIdManual OBJECT-TYPE
            SYNTAX Unsigned32 (0..65535)
            MAX-ACCESS read-write
            STATUS current
            DESCRIPTION
                "The system ID uniquely identifies a T2 system within the DVB-T2 network."
            ::= { dvbt2LocalizationEntry 9 }

        
        dvbt2LocalizationL1FrequencySource OBJECT-TYPE
            SYNTAX Dvbt2L1FrequencySource
            MAX-ACCESS read-write
            STATUS current
            DESCRIPTION
                "See textual convention.
                
                If you select manual(1),
                the value is given with dvbt2LocalizationL1FrequencyManual."
            ::= { dvbt2LocalizationEntry 10 }

        
        dvbt2LocalizationL1FrequencyManual OBJECT-TYPE
            SYNTAX Unsigned32 (0..2000000000)
            UNITS "Hz"
            MAX-ACCESS read-write
            STATUS current
            DESCRIPTION
                "Presetting of L1 frequency shift."
            ::= { dvbt2LocalizationEntry 11 }

        
        dvbt2LocalizationTxDelayOffsetSource OBJECT-TYPE
            SYNTAX Dvbt2TxDelayOffsetSource
            MAX-ACCESS read-write
            STATUS current
            DESCRIPTION
                "See textual convention."
            ::= { dvbt2LocalizationEntry 12 }

        
        dvbt2LocalizationPaprTrSource OBJECT-TYPE
            SYNTAX INTEGER
                {
                off(1),
                manual(2),
                ia(3),
                supported(4)
                }
            MAX-ACCESS read-write
            STATUS current
            DESCRIPTION
                "Description."
            ::= { dvbt2LocalizationEntry 13 }

        
        dvbt2IndividualAddressingTable OBJECT-TYPE
            SYNTAX SEQUENCE OF Dvbt2IndividualAddressingEntry
            MAX-ACCESS not-accessible
            STATUS current
            DESCRIPTION
                "DVB-T2 individual addressing."
            ::= { dvbt2Setup 3 }

        
        dvbt2IndividualAddressingEntry OBJECT-TYPE
            SYNTAX Dvbt2IndividualAddressingEntry
            MAX-ACCESS not-accessible
            STATUS current
            DESCRIPTION
                "An entry in the dvbt2IndividualAddressingTable."
            AUGMENTS { dvbt2ConfigurationEntry }
            ::= { dvbt2IndividualAddressingTable 1 }

        
        Dvbt2IndividualAddressingEntry ::=
            SEQUENCE { 
                dvbt2IaTimeOffset
                    Integer32,
                dvbt2IaTimeOffsetSource
                    Dvbt2IndividualAddressingSource,
                dvbt2IaFrequencyOffset
                    Integer32,
                dvbt2IaFrequencyOffsetSource
                    Dvbt2IndividualAddressingSource,
                dvbt2IaCellID
                    Unsigned32,
                dvbt2IaCellIdSource
                    Dvbt2IndividualAddressingSource
             }

        dvbt2IaTimeOffset OBJECT-TYPE
            SYNTAX Integer32 (-32768..32767)
            UNITS "1/10 micro second"
            MAX-ACCESS read-only
            STATUS current
            DESCRIPTION
                "Shows the transmitting delay for this transmitter in relation to
                other transmitters in the DVB-T2 network.
                This value is defined from the DVB-T2 gateway."
            ::= { dvbt2IndividualAddressingEntry 3 }

        
        dvbt2IaTimeOffsetSource OBJECT-TYPE
            SYNTAX Dvbt2IndividualAddressingSource
            MAX-ACCESS read-only
            STATUS current
            DESCRIPTION
                "Shows the source for the time offset.
                txSpecific(2) - a special time offset was given for this TX identifier
                viaBroadcast(3) - all transmitters of the network got the same
                                  time offset via broadcast"
            ::= { dvbt2IndividualAddressingEntry 4 }

        
        dvbt2IaFrequencyOffset OBJECT-TYPE
            SYNTAX Integer32
            UNITS "Hz"
            MAX-ACCESS read-only
            STATUS current
            DESCRIPTION
                "Shows the frequency shift for this transmitter in relation to
                other transmitters in the DVB-T2 network.
                This value is defined from the DVB-T2 gateway."
            ::= { dvbt2IndividualAddressingEntry 5 }

        
        dvbt2IaFrequencyOffsetSource OBJECT-TYPE
            SYNTAX Dvbt2IndividualAddressingSource
            MAX-ACCESS read-write
            STATUS current
            DESCRIPTION
                "Shows the source for the frequency shift.
                txSpecific(2) - a special frequency shift was given for this TX identifier
                viaBroadcast(3) - all transmitters of the network got the same
                                  frequency shift via broadcast"
            ::= { dvbt2IndividualAddressingEntry 6 }

        
        dvbt2IaCellID OBJECT-TYPE
            SYNTAX Unsigned32 (0..65535)
            MAX-ACCESS read-only
            STATUS current
            DESCRIPTION
                "Shows the cell ID that is given with the individual addressing
                information.
                This value is defined from the DVB-T2 gateway.
                The actual cell ID depends on the setting of dvbt2LocalizationCellIdSource."
            ::= { dvbt2IndividualAddressingEntry 7 }

        
        dvbt2IaCellIdSource OBJECT-TYPE
            SYNTAX Dvbt2IndividualAddressingSource
            MAX-ACCESS read-only
            STATUS current
            DESCRIPTION
                "Shows the source for the cell ID.
                txSpecific(2) - a special cell ID was given for this TX identifier
                viaBroadcast(3) - all transmitters of the network got the same
                                  cell ID via broadcast"
            ::= { dvbt2IndividualAddressingEntry 8 }

        
        dvbt2ChannelTable OBJECT-TYPE
            SYNTAX SEQUENCE OF Dvbt2ChannelEntry
            MAX-ACCESS not-accessible
            STATUS current
            DESCRIPTION
                "DVB-T2 channel parameters."
            ::= { dvbt2Setup 4 }

        
        dvbt2ChannelEntry OBJECT-TYPE
            SYNTAX Dvbt2ChannelEntry
            MAX-ACCESS not-accessible
            STATUS current
            DESCRIPTION
                "An entry in the dvbt2ChannelTable."
            AUGMENTS { dvbt2ConfigurationEntry }
            ::= { dvbt2ChannelTable 1 }

        
        Dvbt2ChannelEntry ::=
            SEQUENCE { 
                dvbt2ChnTransmissionSystem
                    INTEGER,
                dvbt2ChnBandwidth
                    Dvbt2ChannelBandwidth,
                dvbt2ChnFFT
                    Dvbt2FftSize,
                dvbt2ChnFftExtended
                    SwitchOnOff,
                dvbt2ChnGuardInterval
                    Dvbt2GuardInterval,
                dvbt2ChnPilotPattern
                    Dvbt2PilotPattern,
                dvbt2ChnPaprReduction
                    Dvbt2PaprReduction
             }

        dvbt2ChnTransmissionSystem OBJECT-TYPE
            SYNTAX INTEGER
                {
                t2SISO(3),
                t2MISO(4)
                }
            MAX-ACCESS read-write
            STATUS current
            DESCRIPTION
                "Allows to connect several transmitters to a MISO system.
                Only applicable if a T2-MI interface is used.
                A change of this value is possible anytime without signal interruption."
            ::= { dvbt2ChannelEntry 3 }

        
        dvbt2ChnBandwidth OBJECT-TYPE
            SYNTAX Dvbt2ChannelBandwidth
            MAX-ACCESS read-write
            STATUS current
            DESCRIPTION
                "The channel bandwidth that the DVB-T2 signal allocates
                in the frequency spectrum.
                For safety reasons it is always set manually."
            ::= { dvbt2ChannelEntry 4 }

        
        dvbt2ChnFFT OBJECT-TYPE
            SYNTAX Dvbt2FftSize
            MAX-ACCESS read-write
            STATUS current
            DESCRIPTION
                "If a T2-MI interface is used, this value is read-only.
                In this case it is specified by the DVB-T2 gateway."
            ::= { dvbt2ChannelEntry 5 }

        
        dvbt2ChnFftExtended OBJECT-TYPE
            SYNTAX SwitchOnOff
            MAX-ACCESS read-write
            STATUS current
            DESCRIPTION
                "If this field is set to on(1), the extended carrier mode is used.
                If this field is set to off(2), the normal carrier mode is used.
                Only for 8K, 16K or 32K FFT size.
                
                If a T2-MI interface is used, this value is read-only.
                In this case it is specified by the DVB-T2 gateway."
            ::= { dvbt2ChannelEntry 6 }

        
        dvbt2ChnGuardInterval OBJECT-TYPE
            SYNTAX Dvbt2GuardInterval
            MAX-ACCESS read-write
            STATUS current
            DESCRIPTION
                "see textual convention
                
                If a T2-MI interface is used, this value is read-only.
                In this case it is specified by the DVB-T2 gateway."
            ::= { dvbt2ChannelEntry 7 }

        
        dvbt2ChnPilotPattern OBJECT-TYPE
            SYNTAX Dvbt2PilotPattern
            MAX-ACCESS read-write
            STATUS current
            DESCRIPTION
                "see textual convention
                
                If a T2-MI interface is used, this value is read-only.
                In this case it is specified by the DVB-T2 gateway."
            ::= { dvbt2ChannelEntry 8 }

        
        dvbt2ChnPaprReduction OBJECT-TYPE
            SYNTAX Dvbt2PaprReduction
            MAX-ACCESS read-write
            STATUS current
            DESCRIPTION
                "see textual convention
                
                If a T2-MI interface is used, this value is read-only.
                In this case it is specified by the DVB-T2 gateway."
            ::= { dvbt2ChannelEntry 9 }

        
        dvbt2FrameStructureTable OBJECT-TYPE
            SYNTAX SEQUENCE OF Dvbt2FrameStructureEntry
            MAX-ACCESS not-accessible
            STATUS current
            DESCRIPTION
                "DVB-T2 frame structure."
            ::= { dvbt2Setup 5 }

        
        dvbt2FrameStructureEntry OBJECT-TYPE
            SYNTAX Dvbt2FrameStructureEntry
            MAX-ACCESS not-accessible
            STATUS current
            DESCRIPTION
                "An entry in the dvbt2FrameStructureTable."
            AUGMENTS { dvbt2ConfigurationEntry }
            ::= { dvbt2FrameStructureTable 1 }

        
        Dvbt2FrameStructureEntry ::=
            SEQUENCE { 
                dvbt2FsDataSymbolsPerT2Frame
                    Unsigned32,
                dvbt2FsT2FramesPerSuperFrame
                    Unsigned32,
                dvbt2FsT2Version
                    Dvbt2T2Version
             }

        dvbt2FsDataSymbolsPerT2Frame OBJECT-TYPE
            SYNTAX Unsigned32 (1..4095)
            MAX-ACCESS read-write
            STATUS current
            DESCRIPTION
                "The total number of symbols in a frame (excluding P1).
                
                If a T2-MI interface is used, this value is read-only.
                In this case it is specified by the DVB-T2 gateway."
            ::= { dvbt2FrameStructureEntry 3 }

        
        dvbt2FsT2FramesPerSuperFrame OBJECT-TYPE
            SYNTAX Unsigned32 (1..255)
            MAX-ACCESS read-write
            STATUS current
            DESCRIPTION
                "The number of T2-frames in a super-frame is a configurable parameter.
                
                If a T2-MI interface is used, this value is read-only.
                In this case it is specified by the DVB-T2 gateway."
            ::= { dvbt2FrameStructureEntry 4 }

        
        dvbt2FsT2Version OBJECT-TYPE
            SYNTAX Dvbt2T2Version
            MAX-ACCESS read-write
            STATUS current
            DESCRIPTION
                "The T2 version used. If no T2-MI interface is used,
                only version 1.1.1 is supported."
            ::= { dvbt2FrameStructureEntry 5 }

        
        dvbt2L1Table OBJECT-TYPE
            SYNTAX SEQUENCE OF Dvbt2L1Entry
            MAX-ACCESS not-accessible
            STATUS current
            DESCRIPTION
                "DVB-T2 layer 1 parameters."
            ::= { dvbt2Setup 6 }

        
        dvbt2L1Entry OBJECT-TYPE
            SYNTAX Dvbt2L1Entry
            MAX-ACCESS not-accessible
            STATUS current
            DESCRIPTION
                "An entry in the dvbt2L1Table."
            AUGMENTS { dvbt2ConfigurationEntry }
            ::= { dvbt2L1Table 1 }

        
        Dvbt2L1Entry ::=
            SEQUENCE { 
                dvbt2L1Modulation
                    Dvbt2Layer1Modulation,
                dvbt2L1CodeRate
                    Dvbt2Layer1CodeRate,
                dvbt2L1FEC
                    Dvbt2Layer1FEC,
                dvbt2L1Repetition
                    SwitchOnOff
             }

        dvbt2L1Modulation OBJECT-TYPE
            SYNTAX Dvbt2Layer1Modulation
            MAX-ACCESS read-write
            STATUS current
            DESCRIPTION
                "The constellation of the L1-post signalling data block.
                
                If a T2-MI interface is used, this value is read-only.
                In this case it is specified by the DVB-T2 gateway."
            ::= { dvbt2L1Entry 3 }

        
        dvbt2L1CodeRate OBJECT-TYPE
            SYNTAX Dvbt2Layer1CodeRate
            MAX-ACCESS read-write
            STATUS current
            DESCRIPTION
                "The coding of the L1-post signalling data block.
                
                If a T2-MI interface is used, this value is read-only.
                In this case it is specified by the DVB-T2 gateway."
            ::= { dvbt2L1Entry 4 }

        
        dvbt2L1FEC OBJECT-TYPE
            SYNTAX Dvbt2Layer1FEC
            MAX-ACCESS read-write
            STATUS current
            DESCRIPTION
                "The type of the L1 FEC used for the L1-post signalling data block.
                
                If a T2-MI interface is used, this value is read-only.
                In this case it is specified by the DVB-T2 gateway."
            ::= { dvbt2L1Entry 5 }

        
        dvbt2L1Repetition OBJECT-TYPE
            SYNTAX SwitchOnOff
            MAX-ACCESS read-write
            STATUS current
            DESCRIPTION
                "Repetition of L1-post dynamic data.
                
                If a T2-MI interface is used, this value is read-only.
                In this case it is specified by the DVB-T2 gateway."
            ::= { dvbt2L1Entry 6 }

        
        dvbt2Plp1Table OBJECT-TYPE
            SYNTAX SEQUENCE OF Dvbt2Plp1Entry
            MAX-ACCESS not-accessible
            STATUS current
            DESCRIPTION
                "Changeable parameters of the only physical layer pipe
                in case of single PLP mode."
            ::= { dvbt2Setup 7 }

        
        dvbt2Plp1Entry OBJECT-TYPE
            SYNTAX Dvbt2Plp1Entry
            MAX-ACCESS not-accessible
            STATUS current
            DESCRIPTION
                "An entry in the dvbt2PlpTable."
            AUGMENTS { dvbt2ConfigurationEntry }
            ::= { dvbt2Plp1Table 1 }

        
        Dvbt2Plp1Entry ::=
            SEQUENCE { 
                dvbt2Plp1ID
                    Unsigned32,
                dvbt2Plp1GroupID
                    Unsigned32,
                dvbt2Plp1Type
                    Dvbt2PlpType,
                dvbt2Plp1Constellation
                    Dvbt2Modulation,
                dvbt2Plp1Rotation
                    SwitchOnOff,
                dvbt2Plp1CodeRate
                    Dvbt2CodeRate,
                dvbt2Plp1FEC
                    Dvbt2FEC,
                dvbt2Plp1TimeInterleaverType
                    Dvbt2TimeInterleaverType,
                dvbt2Plp1TimeInterleaverLength
                    Unsigned32,
                dvbt2Plp1BasebandMode
                    Dvbt2BasebandMode
             }

        dvbt2Plp1ID OBJECT-TYPE
            SYNTAX Unsigned32 (0..255)
            MAX-ACCESS read-write
            STATUS current
            DESCRIPTION
                "uniquely identifies a PLP within a T2 system"
            ::= { dvbt2Plp1Entry 3 }

        
        dvbt2Plp1GroupID OBJECT-TYPE
            SYNTAX Unsigned32 (0..255)
            MAX-ACCESS read-write
            STATUS current
            DESCRIPTION
                "identifies with which PLP group within the T2 system
                the current PLP is associated. This can be used by a
                receiver to link the data PLP to its associated common PLP,
                which will have the same PLP Group ID.
                "
            ::= { dvbt2Plp1Entry 4 }

        
        dvbt2Plp1Type OBJECT-TYPE
            SYNTAX Dvbt2PlpType
            MAX-ACCESS read-write
            STATUS current
            DESCRIPTION
                "Indicates the set Physical Layer Pipe type."
            ::= { dvbt2Plp1Entry 5 }

        
        dvbt2Plp1Constellation OBJECT-TYPE
            SYNTAX Dvbt2Modulation
            MAX-ACCESS read-write
            STATUS current
            DESCRIPTION
                "Indicates the set modulation mode. 
                QPSK is extremely fail-safe, but has only a low data rate. 
                256QAM can transmit very high data rates and is 
                recommended if few faults are expected on the 
                transmission link. The setting can be changed here.
                "
            ::= { dvbt2Plp1Entry 6 }

        
        dvbt2Plp1Rotation OBJECT-TYPE
            SYNTAX SwitchOnOff
            MAX-ACCESS read-write
            STATUS current
            DESCRIPTION
                "Constellation rotation."
            ::= { dvbt2Plp1Entry 7 }

        
        dvbt2Plp1CodeRate OBJECT-TYPE
            SYNTAX Dvbt2CodeRate
            MAX-ACCESS read-write
            STATUS current
            DESCRIPTION
                "Indicates the set code rate. The code rate is used to set the ratio 
                of information data to <error correction values + information data>. 
                1/2 provides the greatest error correction and the lowest data 
                transfer rate; 
                5/6 provides the lowest error correction and the greatest data 
                transfer rate. The setting can be changed here.
                "
            ::= { dvbt2Plp1Entry 8 }

        
        dvbt2Plp1FEC OBJECT-TYPE
            SYNTAX Dvbt2FEC
            MAX-ACCESS read-write
            STATUS current
            DESCRIPTION
                "Indicates the set error correction algorithm (FEC).  If a T2-MI interface 
                is used, this value is fixed by the DVB-T2 gateway.
                "
            ::= { dvbt2Plp1Entry 9 }

        
        dvbt2Plp1TimeInterleaverType OBJECT-TYPE
            SYNTAX Dvbt2TimeInterleaverType
            MAX-ACCESS read-write
            STATUS current
            DESCRIPTION
                "single(1) - Maps each interleaving frame directly  to a T2 frame.
                multi(2)  - Maps each interleaving frame to more than one T2 frame."
            ::= { dvbt2Plp1Entry 10 }

        
        dvbt2Plp1TimeInterleaverLength OBJECT-TYPE
            SYNTAX Unsigned32 (0..255)
            MAX-ACCESS read-write
            STATUS current
            DESCRIPTION
                "Defines the number of time interleaver blocks (TIB)
                within the time interleaving frame."
            ::= { dvbt2Plp1Entry 11 }

        
        dvbt2Plp1BasebandMode OBJECT-TYPE
            SYNTAX Dvbt2BasebandMode
            MAX-ACCESS read-write
            STATUS current
            DESCRIPTION
                "see textual convention"
            ::= { dvbt2Plp1Entry 12 }

        
        dvbt2TestTable OBJECT-TYPE
            SYNTAX SEQUENCE OF Dvbt2TestEntry
            MAX-ACCESS not-accessible
            STATUS current
            DESCRIPTION
                "Configures the test mode of the exciter."
            ::= { dvbt2Setup 9 }

        
        dvbt2TestEntry OBJECT-TYPE
            SYNTAX Dvbt2TestEntry
            MAX-ACCESS not-accessible
            STATUS current
            DESCRIPTION
                "An entry in the dvbt2TestTable."
            AUGMENTS { dvbt2ConfigurationEntry }
            ::= { dvbt2TestTable 1 }

        
        Dvbt2TestEntry ::=
            SEQUENCE { 
                dvbt2TestGeneration
                    SwitchOnOff,
                dvbt2TestMode
                    INTEGER
             }

        dvbt2TestGeneration OBJECT-TYPE
            SYNTAX SwitchOnOff
            MAX-ACCESS read-write
            STATUS obsolete
            DESCRIPTION
                "Switches test signal generation on or off.
                A test signal enables measurements for the transmitter
                if no valid DVB-T2 input exists or
                the DVB-T2 option is not active."
            ::= { dvbt2TestEntry 3 }

        
        dvbt2TestMode OBJECT-TYPE
            SYNTAX INTEGER
                {
                off(1),
                prbs(2),
                singleCarrier(3),
                mute1P1SymOfSuperFrame(6)
                }
            MAX-ACCESS read-write
            STATUS current
            DESCRIPTION
                "Indicates which test signal is generated. 
                
                off: Switches off test signal generation. 
                
                PRBS:Generates a PRBS sequence instead of the payload. 
                
                Mute 1st P1 Symbol: Suppresses the first symbol of each T2 frame. This function 
                can be used to measure the time of signal transmission. 
                
                Single Carrier: Generates an unmodulated single carrier. The frequency of the 
                single carrier is at the center of the band and therefore deviates from the vision 
                carrier frequency. This test signal can be used to measure the phase noise of the 
                synthesizer. The phase noise must be measured via the RF Monitor Out 
                connector (X61). The cable connected to RF Out (X60) must be removed. In order 
                to protect the amplifiers, this test signal is only generated if the output of the 
                exciter is open. 
                "
            ::= { dvbt2TestEntry 4 }

        
        dvbt2Output OBJECT IDENTIFIER ::= { rsXx9Dvbt2Objects 3 }

        
        dvbt2OutLocalizationTable OBJECT-TYPE
            SYNTAX SEQUENCE OF Dvbt2OutLocalizationEntry
            MAX-ACCESS not-accessible
            STATUS current
            DESCRIPTION
                "DVB-T2 localization
                as signalled from the DVB-T2 gateway."
            ::= { dvbt2Output 2 }

        
        dvbt2OutLocalizationEntry OBJECT-TYPE
            SYNTAX Dvbt2OutLocalizationEntry
            MAX-ACCESS not-accessible
            STATUS current
            DESCRIPTION
                "An entry in the dvbt2OutLocalizationTable."
            AUGMENTS { dvbt2ConfigurationEntry }
            ::= { dvbt2OutLocalizationTable 1 }

        
        Dvbt2OutLocalizationEntry ::=
            SEQUENCE { 
                dvbt2OutLocalizationCellIdSource
                    Dvbt2CellIdSource,
                dvbt2OutLocalizationCellId
                    Unsigned32,
                dvbt2OutLocalizationMisoGroupSource
                    INTEGER,
                dvbt2OutLocalizationMisoGroup
                    INTEGER,
                dvbt2OutLocalizationNetworkId
                    Unsigned32,
                dvbt2OutLocalizationSystemId
                    Unsigned32,
                dvbt2OutLocalizationL1FrequencySource
                    Dvbt2L1FrequencySource,
                dvbt2OutLocalizationL1Frequency
                    Unsigned32,
                dvbt2OutLocalizationTxDelayOffsetSource
                    Dvbt2TxDelayOffsetSource,
                dvbt2OutLocalizationTxDelayOffset
                    Integer32,
                dvbt2OutLocalizationPaprTrSource
                    INTEGER
             }

        dvbt2OutLocalizationCellIdSource OBJECT-TYPE
            SYNTAX Dvbt2CellIdSource
            MAX-ACCESS read-only
            STATUS current
            DESCRIPTION
                "See textual convention."
            ::= { dvbt2OutLocalizationEntry 1 }

        
        dvbt2OutLocalizationCellId OBJECT-TYPE
            SYNTAX Unsigned32
            MAX-ACCESS read-only
            STATUS current
            DESCRIPTION
                "The cell ID that is actually transmitted."
            ::= { dvbt2OutLocalizationEntry 3 }

        
        dvbt2OutLocalizationMisoGroupSource OBJECT-TYPE
            SYNTAX INTEGER
                {
                off(1),
                manual(2),
                ia(3)
                }
            MAX-ACCESS read-only
            STATUS current
            DESCRIPTION
                "Source for the MISO group:
                manual(2) - from dvbt2LocalizationMisoGroupManual
                ia(3)     - from the individual addressing data
                            of the DVB-T2 gateway stream"
            ::= { dvbt2OutLocalizationEntry 4 }

        
        dvbt2OutLocalizationMisoGroup OBJECT-TYPE
            SYNTAX INTEGER
                {
                unused(3),
                group1(4),
                group2(5)
                }
            MAX-ACCESS read-only
            STATUS current
            DESCRIPTION
                "The actual MISO group for the transmitter.
                In a MISO system the two transmitters have to be assigned
                different groups.
                In a SFN system several transmitters may belong to one group."
            ::= { dvbt2OutLocalizationEntry 5 }

        
        dvbt2OutLocalizationNetworkId OBJECT-TYPE
            SYNTAX Unsigned32
            MAX-ACCESS read-only
            STATUS current
            DESCRIPTION
                "The actual network ID for the transmitter."
            ::= { dvbt2OutLocalizationEntry 6 }

        
        dvbt2OutLocalizationSystemId OBJECT-TYPE
            SYNTAX Unsigned32
            MAX-ACCESS read-only
            STATUS current
            DESCRIPTION
                "The actual system ID for the transmitter."
            ::= { dvbt2OutLocalizationEntry 7 }

        
        dvbt2OutLocalizationL1FrequencySource OBJECT-TYPE
            SYNTAX Dvbt2L1FrequencySource
            MAX-ACCESS read-only
            STATUS current
            DESCRIPTION
                "See textual convention."
            ::= { dvbt2OutLocalizationEntry 8 }

        
        dvbt2OutLocalizationL1Frequency OBJECT-TYPE
            SYNTAX Unsigned32
            UNITS "Hz"
            MAX-ACCESS read-only
            STATUS current
            DESCRIPTION
                "Currently used L1 frequency with index 0."
            ::= { dvbt2OutLocalizationEntry 9 }

        
        dvbt2OutLocalizationTxDelayOffsetSource OBJECT-TYPE
            SYNTAX Dvbt2TxDelayOffsetSource
            MAX-ACCESS read-only
            STATUS current
            DESCRIPTION
                "See textual convention."
            ::= { dvbt2OutLocalizationEntry 10 }

        
        dvbt2OutLocalizationTxDelayOffset OBJECT-TYPE
            SYNTAX Integer32
            UNITS "1/10 micro second"
            MAX-ACCESS read-only
            STATUS current
            DESCRIPTION
                "Transmitter specific transmitting delay."
            ::= { dvbt2OutLocalizationEntry 11 }

        
        dvbt2OutLocalizationPaprTrSource OBJECT-TYPE
            SYNTAX INTEGER
                {
                off(1),
                manual(2),
                ia(3),
                supported(4)
                }
            MAX-ACCESS read-write
            STATUS current
            DESCRIPTION
                "Description."
            ::= { dvbt2OutLocalizationEntry 12 }

        
        dvbt2OutChannelTable OBJECT-TYPE
            SYNTAX SEQUENCE OF Dvbt2OutChannelEntry
            MAX-ACCESS not-accessible
            STATUS current
            DESCRIPTION
                "DVB-T2 channel parameters
                as signalled from the DVB-T2 gateway."
            ::= { dvbt2Output 4 }

        
        dvbt2OutChannelEntry OBJECT-TYPE
            SYNTAX Dvbt2OutChannelEntry
            MAX-ACCESS not-accessible
            STATUS current
            DESCRIPTION
                "An entry in the dvbt2OutChannelTable."
            AUGMENTS { dvbt2ConfigurationEntry }
            ::= { dvbt2OutChannelTable 1 }

        
        Dvbt2OutChannelEntry ::=
            SEQUENCE { 
                dvbt2OutChnTransmissionSystem
                    Dvbt2TransmissionSystem,
                dvbt2OutChnBandwidth
                    Dvbt2ChannelBandwidth,
                dvbt2OutChnFFT
                    Dvbt2FftSize,
                dvbt2OutChnFftExtended
                    Dvbt2OnOff,
                dvbt2OutChnGuardInterval
                    Dvbt2GuardInterval,
                dvbt2OutChnPilotPattern
                    Dvbt2PilotPattern,
                dvbt2OutChnPaprReduction
                    Dvbt2PaprReduction,
                dvbt2OutChnT2BaseLite
                    Dvbt2OnOff,
                dvbt2OutChnPreamble
                    INTEGER,
                dvbt2OutChnInputStreamTypes
                    INTEGER,
                dvbt2OutChnRegenerationFlag
                    Unsigned32,
                dvbt2OutChnT2Profile
                    INTEGER
             }

        dvbt2OutChnTransmissionSystem OBJECT-TYPE
            SYNTAX Dvbt2TransmissionSystem
            MAX-ACCESS read-only
            STATUS current
            DESCRIPTION
                "see textual convention"
            ::= { dvbt2OutChannelEntry 3 }

        
        dvbt2OutChnBandwidth OBJECT-TYPE
            SYNTAX Dvbt2ChannelBandwidth
            MAX-ACCESS read-only
            STATUS current
            DESCRIPTION
                "The channel bandwidth as signalled by the DVB-T2 gateway."
            ::= { dvbt2OutChannelEntry 4 }

        
        dvbt2OutChnFFT OBJECT-TYPE
            SYNTAX Dvbt2FftSize
            MAX-ACCESS read-only
            STATUS current
            DESCRIPTION
                "see textual convention"
            ::= { dvbt2OutChannelEntry 5 }

        
        dvbt2OutChnFftExtended OBJECT-TYPE
            SYNTAX Dvbt2OnOff
            MAX-ACCESS read-only
            STATUS current
            DESCRIPTION
                "When this field is on(1), the extended carrier mode is used.
                If this field is off(2), the normal carrier mode is used.
                Only for 8K, 16K or 32K FFT size."
            ::= { dvbt2OutChannelEntry 6 }

        
        dvbt2OutChnGuardInterval OBJECT-TYPE
            SYNTAX Dvbt2GuardInterval
            MAX-ACCESS read-only
            STATUS current
            DESCRIPTION
                "see textual convention"
            ::= { dvbt2OutChannelEntry 7 }

        
        dvbt2OutChnPilotPattern OBJECT-TYPE
            SYNTAX Dvbt2PilotPattern
            MAX-ACCESS read-only
            STATUS current
            DESCRIPTION
                "see textual convention"
            ::= { dvbt2OutChannelEntry 8 }

        
        dvbt2OutChnPaprReduction OBJECT-TYPE
            SYNTAX Dvbt2PaprReduction
            MAX-ACCESS read-only
            STATUS current
            DESCRIPTION
                "see textual convention"
            ::= { dvbt2OutChannelEntry 9 }

        
        dvbt2OutChnT2BaseLite OBJECT-TYPE
            SYNTAX Dvbt2OnOff
            MAX-ACCESS read-only
            STATUS current
            DESCRIPTION
                "Shows whether the sent out T2-Base profile is compatible
                with a T2-LITE profile."
            ::= { dvbt2OutChannelEntry 10 }

        
        dvbt2OutChnPreamble OBJECT-TYPE
            SYNTAX INTEGER
                {
                undefined(1),
                notMixed(3),
                mixed(4)
                }
            MAX-ACCESS read-write
            STATUS current
            DESCRIPTION
                "Indicates whether the preambles are all of the same type or not:
                notMixed(3) - all preambles in the current transmission are of the same type
                mixed(4)    - preambles of different types are transmitted"
            ::= { dvbt2OutChannelEntry 11 }

        
        dvbt2OutChnInputStreamTypes OBJECT-TYPE
            SYNTAX INTEGER
                {
                undefined(1),
                tsOnly(3),
                gsOnly(4),
                tsAndGs(5)
                }
            MAX-ACCESS read-only
            STATUS current
            DESCRIPTION
                "The types of the Tx input streams carried within the T2 super-frame:
                tsOnly(3)  - transport stream (TS) only
                gsOnly(4)  - generic stream, but not TS
                tsAndGs(5) - both TS and generic stream"
            ::= { dvbt2OutChannelEntry 12 }

        
        dvbt2OutChnRegenerationFlag OBJECT-TYPE
            SYNTAX Unsigned32
            MAX-ACCESS read-only
            STATUS current
            DESCRIPTION
                "Indicates how many times the DVB-T2 signal has been re-generated.
                Value 0 indicates that no regeneration has been done.
                Each time the DVB-T2 signal is regenerated this field is increased by one."
            ::= { dvbt2OutChannelEntry 13 }

        
        dvbt2OutChnT2Profile OBJECT-TYPE
            SYNTAX INTEGER
                {
                undefined(1),
                base(3),
                baseLite(4),
                lite(5)
                }
            MAX-ACCESS read-only
            STATUS current
            DESCRIPTION
                "The T2-profile used. The standard profile is T2-Base,
                while T2-Lite has been introduced in T2 version 1.3.1.
                T2-Lite is intended for mobile applications.
                The T2-Base-Lite option is the intersection between T2-Base and T2-Lite,
                i.e. a signal that is valid for both T2-Base and T2-Lite profiles.
                The T2-Base-Lite profile will be signalled as a normal T2-Base signal,
                but with the T2_BASE_LITE flag set in the L1-Pre signaling."
            ::= { dvbt2OutChannelEntry 14 }

        
        dvbt2OutFrameStructureTable OBJECT-TYPE
            SYNTAX SEQUENCE OF Dvbt2OutFrameStructureEntry
            MAX-ACCESS not-accessible
            STATUS current
            DESCRIPTION
                "DVB-T2 frame structure
                as signalled from the DVB-T2 gateway."
            ::= { dvbt2Output 5 }

        
        dvbt2OutFrameStructureEntry OBJECT-TYPE
            SYNTAX Dvbt2OutFrameStructureEntry
            MAX-ACCESS not-accessible
            STATUS current
            DESCRIPTION
                "An entry in the dvbt2OutFrameStructureTable."
            AUGMENTS { dvbt2ConfigurationEntry }
            ::= { dvbt2OutFrameStructureTable 1 }

        
        Dvbt2OutFrameStructureEntry ::=
            SEQUENCE { 
                dvbt2OutFsDataSymbolsPerT2Frame
                    Unsigned32,
                dvbt2OutFsT2FramesPerSuperFrame
                    Unsigned32,
                dvbt2OutFsT2Version
                    Dvbt2T2Version,
                dvbt2OutFsSubSlicesPerFrame
                    Unsigned32,
                dvbt2OutFsNumOfPLP
                    Unsigned32,
                dvbt2OutFsNumOfAux
                    Unsigned32
             }

        dvbt2OutFsDataSymbolsPerT2Frame OBJECT-TYPE
            SYNTAX Unsigned32
            MAX-ACCESS read-only
            STATUS current
            DESCRIPTION
                "The total number of symbols in a frame (excluding P1).
                
                If a T2-MI interface is used, this value is read-only.
                In this case it is specified by the DVB-T2 gateway."
            ::= { dvbt2OutFrameStructureEntry 3 }

        
        dvbt2OutFsT2FramesPerSuperFrame OBJECT-TYPE
            SYNTAX Unsigned32
            MAX-ACCESS read-only
            STATUS current
            DESCRIPTION
                "The number of T2-frames in a super-frame is a configurable parameter.
                
                If a T2-MI interface is used, this value is read-only.
                In this case it is specified by the DVB-T2 gateway."
            ::= { dvbt2OutFrameStructureEntry 4 }

        
        dvbt2OutFsT2Version OBJECT-TYPE
            SYNTAX Dvbt2T2Version
            MAX-ACCESS read-only
            STATUS current
            DESCRIPTION
                "If no T2-MI interface is used only version 1.1.1 is supported."
            ::= { dvbt2OutFrameStructureEntry 5 }

        
        dvbt2OutFsSubSlicesPerFrame OBJECT-TYPE
            SYNTAX Unsigned32
            MAX-ACCESS read-only
            STATUS current
            DESCRIPTION
                "The total number of sub-slices for the type 2 data PLPs
                across all RF channels in one T2-frame."
            ::= { dvbt2OutFrameStructureEntry 6 }

        
        dvbt2OutFsNumOfPLP OBJECT-TYPE
            SYNTAX Unsigned32
            MAX-ACCESS read-only
            STATUS current
            DESCRIPTION
                "The number of PLPs carried within the super-frame."
            ::= { dvbt2OutFrameStructureEntry 7 }

        
        dvbt2OutFsNumOfAux OBJECT-TYPE
            SYNTAX Unsigned32
            MAX-ACCESS read-only
            STATUS current
            DESCRIPTION
                "number of auxiliary streams"
            ::= { dvbt2OutFrameStructureEntry 8 }

        
        dvbt2OutL1Table OBJECT-TYPE
            SYNTAX SEQUENCE OF Dvbt2OutL1Entry
            MAX-ACCESS not-accessible
            STATUS current
            DESCRIPTION
                "DVB-T2 layer 1 parameters
                as signalled from the DVB-T2 gateway."
            ::= { dvbt2Output 6 }

        
        dvbt2OutL1Entry OBJECT-TYPE
            SYNTAX Dvbt2OutL1Entry
            MAX-ACCESS not-accessible
            STATUS current
            DESCRIPTION
                "An entry in the dvbt2OutL1Table."
            AUGMENTS { dvbt2ConfigurationEntry }
            ::= { dvbt2OutL1Table 1 }

        
        Dvbt2OutL1Entry ::=
            SEQUENCE { 
                dvbt2OutL1Modulation
                    Dvbt2Layer1Modulation,
                dvbt2OutL1CodeRate
                    Dvbt2Layer1CodeRate,
                dvbt2OutL1FEC
                    Dvbt2Layer1FEC,
                dvbt2OutL1Repetition
                    Dvbt2OnOff,
                dvbt2OutL1PostScrambled
                    Dvbt2OnOff,
                dvbt2OutL1PostExtension
                    Dvbt2OnOff
             }

        dvbt2OutL1Modulation OBJECT-TYPE
            SYNTAX Dvbt2Layer1Modulation
            MAX-ACCESS read-only
            STATUS current
            DESCRIPTION
                "The constellation of the L1-post signalling data block."
            ::= { dvbt2OutL1Entry 3 }

        
        dvbt2OutL1CodeRate OBJECT-TYPE
            SYNTAX Dvbt2Layer1CodeRate
            MAX-ACCESS read-only
            STATUS current
            DESCRIPTION
                "The coding of the L1-post signalling data block."
            ::= { dvbt2OutL1Entry 4 }

        
        dvbt2OutL1FEC OBJECT-TYPE
            SYNTAX Dvbt2Layer1FEC
            MAX-ACCESS read-only
            STATUS current
            DESCRIPTION
                "The type of the L1 FEC used for the L1-post signalling data block."
            ::= { dvbt2OutL1Entry 5 }

        
        dvbt2OutL1Repetition OBJECT-TYPE
            SYNTAX Dvbt2OnOff
            MAX-ACCESS read-only
            STATUS current
            DESCRIPTION
                "Repetition of L1-post dynamic data."
            ::= { dvbt2OutL1Entry 6 }

        
        dvbt2OutL1PostScrambled OBJECT-TYPE
            SYNTAX Dvbt2OnOff
            MAX-ACCESS read-only
            STATUS current
            DESCRIPTION
                "Shows whether signalling of L1-post is scrambled."
            ::= { dvbt2OutL1Entry 7 }

        
        dvbt2OutL1PostExtension OBJECT-TYPE
            SYNTAX Dvbt2OnOff
            MAX-ACCESS read-only
            STATUS current
            DESCRIPTION
                "Indicates the presence of the L1-post extension field."
            ::= { dvbt2OutL1Entry 8 }

        
        dvbt2OutPlpTable OBJECT-TYPE
            SYNTAX SEQUENCE OF Dvbt2OutPlpEntry
            MAX-ACCESS not-accessible
            STATUS current
            DESCRIPTION
                "DVB-T2 PLP parameters
                as signalled from the DVB-T2 gateway."
            ::= { dvbt2Output 7 }

        
        dvbt2OutPlpEntry OBJECT-TYPE
            SYNTAX Dvbt2OutPlpEntry
            MAX-ACCESS not-accessible
            STATUS current
            DESCRIPTION
                "An entry in the dvbt2OutPlpTable."
            INDEX { dvbt2ConfigurationTxIdx, dvbt2ConfigurationExcIdx, dvbt2OutPlpIdx }
            ::= { dvbt2OutPlpTable 1 }

        
        Dvbt2OutPlpEntry ::=
            SEQUENCE { 
                dvbt2OutPlpIdx
                    Unsigned32,
                dvbt2OutPlpID
                    Unsigned32,
                dvbt2OutPlpGroupID
                    Unsigned32,
                dvbt2OutPlpType
                    Dvbt2PlpType,
                dvbt2OutPlpPayloadType
                    INTEGER,
                dvbt2OutPlpConstellation
                    Dvbt2Modulation,
                dvbt2OutPlpRotation
                    Dvbt2OnOff,
                dvbt2OutPlpCodeRate
                    Dvbt2CodeRate,
                dvbt2OutPlpFEC
                    Dvbt2FEC,
                dvbt2OutPlpFecBlocks
                    Unsigned32,
                dvbt2OutPlpTimeInterleaverType
                    Dvbt2TimeInterleaverType,
                dvbt2OutPlpTimeInterleaverLength
                    Unsigned32,
                dvbt2OutPlpBasebandMode
                    Dvbt2BasebandMode,
                dvbt2OutPlpFrameInterval
                    Unsigned32,
                dvbt2OutPlpBasebandPayloadPadding
                    Dvbt2OnOff,
                dvbt2OutPlpNullPacketDeletion
                    Dvbt2OnOff,
                dvbt2OutPlpNumOfOtherPlpInBand
                    Unsigned32,
                dvbt2OutPlpCmType
                    INTEGER,
                dvbt2OutPlpISSY
                    INTEGER,
                dvbt2OutPlpInBandFlag
                    Dvbt2OnOff,
                dvbt2OutPlpInBandASig
                    Dvbt2OnOff,
                dvbt2OutPlpInBandBSig
                    Dvbt2OnOff
             }

        dvbt2OutPlpIdx OBJECT-TYPE
            SYNTAX Unsigned32 (1..8)
            MAX-ACCESS not-accessible
            STATUS current
            DESCRIPTION
                "The PLP number.
                This is a helper column and therefore not-accessible."
            ::= { dvbt2OutPlpEntry 2 }

        
        dvbt2OutPlpID OBJECT-TYPE
            SYNTAX Unsigned32
            MAX-ACCESS read-only
            STATUS current
            DESCRIPTION
                "uniquely identifies a PLP within a T2 system"
            ::= { dvbt2OutPlpEntry 3 }

        
        dvbt2OutPlpGroupID OBJECT-TYPE
            SYNTAX Unsigned32
            MAX-ACCESS read-only
            STATUS current
            DESCRIPTION
                "identifies with which PLP group within the T2 system
                the current PLP is associated. This can be used by a
                receiver to link the data PLP to its associated common PLP,
                which will have the same PLP Group ID.
                "
            ::= { dvbt2OutPlpEntry 4 }

        
        dvbt2OutPlpType OBJECT-TYPE
            SYNTAX Dvbt2PlpType
            MAX-ACCESS read-only
            STATUS current
            DESCRIPTION
                "Indicates the set Physical Layer Pipe type."
            ::= { dvbt2OutPlpEntry 5 }

        
        dvbt2OutPlpPayloadType OBJECT-TYPE
            SYNTAX INTEGER
                {
                reserved(2),
                gfps(3),
                gcs(4),
                gse(5),
                ts(6)
                }
            MAX-ACCESS read-only
            STATUS current
            DESCRIPTION
                "Each input PLP may take one of the following formats:
                gfps(3) - Generic Fixed-length Packetized Stream
                          This form is retained for compatibility with DVB-S2,
                          but it is expected that GSE would now be used instead.
                gcs(4)  - Generic Continuous Stream
                          A variable length packet stream where the modulator
                          is not aware of the packet boundaries.
                gse(5)  - Generic Encapsulated Stream
                ts(6)   - Transport Stream"
            ::= { dvbt2OutPlpEntry 6 }

        
        dvbt2OutPlpConstellation OBJECT-TYPE
            SYNTAX Dvbt2Modulation
            MAX-ACCESS read-only
            STATUS current
            DESCRIPTION
                "Indicates the set modulation mode. 
                QPSK is extremely fail-safe, but has only a low data rate. 
                256QAM can transmit very high data rates and is 
                recommended if few faults are expected on the 
                transmission link. 
                "
            ::= { dvbt2OutPlpEntry 7 }

        
        dvbt2OutPlpRotation OBJECT-TYPE
            SYNTAX Dvbt2OnOff
            MAX-ACCESS read-only
            STATUS current
            DESCRIPTION
                "Constellation rotation."
            ::= { dvbt2OutPlpEntry 8 }

        
        dvbt2OutPlpCodeRate OBJECT-TYPE
            SYNTAX Dvbt2CodeRate
            MAX-ACCESS read-only
            STATUS current
            DESCRIPTION
                "Indicates the set code rate. The code rate is used to set the ratio 
                of information data to <error correction values + information data>. 
                1/2 provides the greatest error correction and the lowest data 
                transfer rate; 
                5/6 provides the lowest error correction and the greatest data 
                transfer rate.
                "
            ::= { dvbt2OutPlpEntry 9 }

        
        dvbt2OutPlpFEC OBJECT-TYPE
            SYNTAX Dvbt2FEC
            MAX-ACCESS read-only
            STATUS current
            DESCRIPTION
                "Indicates the set error correction algorithm (FEC).  If a T2-MI interface 
                is used, this value is fixed by the DVB-T2 gateway.
                "
            ::= { dvbt2OutPlpEntry 10 }

        
        dvbt2OutPlpFecBlocks OBJECT-TYPE
            SYNTAX Unsigned32
            MAX-ACCESS read-only
            STATUS obsolete
            DESCRIPTION
                "Displays the received number of maximum FEC blocks per interleaving frame.
                obsoleted"
            ::= { dvbt2OutPlpEntry 11 }

        
        dvbt2OutPlpTimeInterleaverType OBJECT-TYPE
            SYNTAX Dvbt2TimeInterleaverType
            MAX-ACCESS read-only
            STATUS current
            DESCRIPTION
                "single(1) - Maps each interleaving frame directly  to a T2 frame.
                multi(2)  - Maps each interleaving frame to more than one T2 frame."
            ::= { dvbt2OutPlpEntry 12 }

        
        dvbt2OutPlpTimeInterleaverLength OBJECT-TYPE
            SYNTAX Unsigned32
            MAX-ACCESS read-only
            STATUS current
            DESCRIPTION
                "Defines the number of time interleaver blocks (TIB)
                within the time interleaving frame."
            ::= { dvbt2OutPlpEntry 13 }

        
        dvbt2OutPlpBasebandMode OBJECT-TYPE
            SYNTAX Dvbt2BasebandMode
            MAX-ACCESS read-only
            STATUS current
            DESCRIPTION
                "see textual convention"
            ::= { dvbt2OutPlpEntry 14 }

        
        dvbt2OutPlpFrameInterval OBJECT-TYPE
            SYNTAX Unsigned32
            MAX-ACCESS read-only
            STATUS current
            DESCRIPTION
                "Indicates the T2-frame interval within the super-frame
                for the associated PLP."
            ::= { dvbt2OutPlpEntry 15 }

        
        dvbt2OutPlpBasebandPayloadPadding OBJECT-TYPE
            SYNTAX Dvbt2OnOff
            MAX-ACCESS read-only
            STATUS current
            DESCRIPTION
                "Shows whether frame padding is used in base band
                for achieving constant length of base band frame."
            ::= { dvbt2OutPlpEntry 16 }

        
        dvbt2OutPlpNullPacketDeletion OBJECT-TYPE
            SYNTAX Dvbt2OnOff
            MAX-ACCESS read-only
            STATUS current
            DESCRIPTION
                "Shows whether null packets (PID=8191) including the optional
                ISSY field are deleted."
            ::= { dvbt2OutPlpEntry 17 }

        
        dvbt2OutPlpNumOfOtherPlpInBand OBJECT-TYPE
            SYNTAX Unsigned32
            MAX-ACCESS read-only
            STATUS current
            DESCRIPTION
                "If equal 0, the relevant PLP carries only its own in-band L1 dynamic information. 
                If greater 0, it carries L1 dynamic information of other PLPs as well as its own
                information, for shorter channel switching time."
            ::= { dvbt2OutPlpEntry 18 }

        
        dvbt2OutPlpCmType OBJECT-TYPE
            SYNTAX INTEGER
                {
                undefined(1),
                aCM(3),
                cCM(4)
                }
            MAX-ACCESS read-only
            STATUS current
            DESCRIPTION
                "Coding and modulation type:
                Code rate, constellation and rotation
                aCM(3) - may be different for different PLPs
                cCM(4) - are equal for all PLPs"
            ::= { dvbt2OutPlpEntry 19 }

        
        dvbt2OutPlpISSY OBJECT-TYPE
            SYNTAX INTEGER
                {
                undefined(1),
                off(3),
                short(4),
                long(5)
                }
            MAX-ACCESS read-only
            STATUS obsolete
            DESCRIPTION
                "Input stream synchronization:
                shows whether ISSY information is included
                off(3)   - no ISSY information
                short(4) - 16 bit ISSY information
                long(5)  - 24 bit ISSY information
                
                obsoleted"
            ::= { dvbt2OutPlpEntry 20 }

        
        dvbt2OutPlpInBandFlag OBJECT-TYPE
            SYNTAX Dvbt2OnOff
            MAX-ACCESS read-only
            STATUS current
            DESCRIPTION
                "Indicates whether the padding carries in-band signalling information.
                (Available with T2-Version 1.1.1)"
            ::= { dvbt2OutPlpEntry 21 }

        
        dvbt2OutPlpInBandASig OBJECT-TYPE
            SYNTAX Dvbt2OnOff
            MAX-ACCESS read-only
            STATUS current
            DESCRIPTION
                "Indicates whether the padding carries in-band signalling information
                of type A.
                (Available with T2-Version 1.2.1 or higher)"
            ::= { dvbt2OutPlpEntry 22 }

        
        dvbt2OutPlpInBandBSig OBJECT-TYPE
            SYNTAX Dvbt2OnOff
            MAX-ACCESS read-only
            STATUS current
            DESCRIPTION
                "Indicates whether the padding carries in-band signalling information
                of type B.
                (Available with T2-Version 1.2.1 or higher)"
            ::= { dvbt2OutPlpEntry 23 }

        
        dvbt2OutPaprTrTable OBJECT-TYPE
            SYNTAX SEQUENCE OF Dvbt2OutPaprTrEntry
            MAX-ACCESS not-accessible
            STATUS current
            DESCRIPTION
                "PAPR (Peak to Average Power Ratio) reduction using tone reservation parameters."
            ::= { dvbt2Output 8 }

        
        dvbt2OutPaprTrEntry OBJECT-TYPE
            SYNTAX Dvbt2OutPaprTrEntry
            MAX-ACCESS not-accessible
            STATUS current
            DESCRIPTION
                "An entry in the dvbt2OutPaprTrTable."
            AUGMENTS { dvbt2ConfigurationEntry }
            ::= { dvbt2OutPaprTrTable 1 }

        
        Dvbt2OutPaprTrEntry ::=
            SEQUENCE { 
                dvbt2OutPaprTrIterations
                    Unsigned32,
                dvbt2OutPaprTrClippingThreshold
                    Unsigned32,
                dvbt2OutPaprTrIterationsSupported
                    Unsigned32,
                dvbt2OutPaprTrIterationsIA
                    Unsigned32,
                dvbt2OutPaprTrIterationsReduced
                    TruthValue,
                dvbt2OutPaprTrIterationsActive
                    Unsigned32
             }

        dvbt2OutPaprTrIterations OBJECT-TYPE
            SYNTAX Unsigned32
            MAX-ACCESS read-only
            STATUS current
            DESCRIPTION
                "Indicates the maximum number of tone reservation repetitions 
                that are supported by the currently selected Bandwidth, FFT 
                and Guard Interval settings.
                "
            ::= { dvbt2OutPaprTrEntry 1 }

        
        dvbt2OutPaprTrClippingThreshold OBJECT-TYPE
            SYNTAX Unsigned32
            MAX-ACCESS read-only
            STATUS current
            DESCRIPTION
                "Indicates the limit up to which the PAPR-TR algorithm operates. 
                The displayed value divided by 100 roughly corresponds to the 
                desired crest factor in dB.
                "
            ::= { dvbt2OutPaprTrEntry 2 }

        
        dvbt2OutPaprTrIterationsSupported OBJECT-TYPE
            SYNTAX Unsigned32
            MAX-ACCESS read-only
            STATUS current
            DESCRIPTION
                "Maximum number of iterations of tone reservation that are supported
                for the adjusted bandwidth, FFT and guard interval."
            ::= { dvbt2OutPaprTrEntry 3 }

        
        dvbt2OutPaprTrIterationsIA OBJECT-TYPE
            SYNTAX Unsigned32
            MAX-ACCESS read-only
            STATUS current
            DESCRIPTION
                "Description."
            ::= { dvbt2OutPaprTrEntry 4 }

        
        dvbt2OutPaprTrIterationsReduced OBJECT-TYPE
            SYNTAX TruthValue
            MAX-ACCESS read-only
            STATUS current
            DESCRIPTION
                "The number of iterations signalled by IA is too high.
                The number of active iterations is reduced to the number of supported iterations."
            ::= { dvbt2OutPaprTrEntry 5 }

        
        dvbt2OutPaprTrIterationsActive OBJECT-TYPE
            SYNTAX Unsigned32
            MAX-ACCESS read-only
            STATUS current
            DESCRIPTION
                "Number of iterations of tone reservations per symbol."
            ::= { dvbt2OutPaprTrEntry 6 }

        
        dvbt2OutFefTable OBJECT-TYPE
            SYNTAX SEQUENCE OF Dvbt2OutFefEntry
            MAX-ACCESS not-accessible
            STATUS current
            DESCRIPTION
                "FEF (future extension frame) values."
            ::= { dvbt2Output 9 }

        
        dvbt2OutFefEntry OBJECT-TYPE
            SYNTAX Dvbt2OutFefEntry
            MAX-ACCESS not-accessible
            STATUS current
            DESCRIPTION
                "An entry in the dvbt2OutFefTable."
            AUGMENTS { dvbt2ConfigurationEntry }
            ::= { dvbt2OutFefTable 1 }

        
        Dvbt2OutFefEntry ::=
            SEQUENCE { 
                dvbt2OutFefOn
                    Dvbt2OnOff,
                dvbt2OutFefType
                    Unsigned32,
                dvbt2OutFefLength
                    Unsigned32,
                dvbt2OutFefInterval
                    Unsigned32
             }

        dvbt2OutFefOn OBJECT-TYPE
            SYNTAX Dvbt2OnOff
            MAX-ACCESS read-only
            STATUS current
            DESCRIPTION
                "Indicates whether future extension frames are used."
            ::= { dvbt2OutFefEntry 1 }

        
        dvbt2OutFefType OBJECT-TYPE
            SYNTAX Unsigned32
            MAX-ACCESS read-only
            STATUS current
            DESCRIPTION
                "Indicates the type of the associated FEF part as a digit."
            ::= { dvbt2OutFefEntry 2 }

        
        dvbt2OutFefLength OBJECT-TYPE
            SYNTAX Unsigned32
            MAX-ACCESS read-only
            STATUS current
            DESCRIPTION
                "Indicates the length of the used FEF part as the number of periods T from the 
                beginning of the P1 symbol of the FEF part to the beginning of the P1 symbol 
                of the next T2 frame."
            ::= { dvbt2OutFefEntry 3 }

        
        dvbt2OutFefInterval OBJECT-TYPE
            SYNTAX Unsigned32
            MAX-ACCESS read-only
            STATUS current
            DESCRIPTION
                "Indicates the number of T2-frames between two FEF parts."
            ::= { dvbt2OutFefEntry 4 }

        
        dvbt2CoderSub OBJECT IDENTIFIER ::= { rsXx9Dvbt2Objects 10 }

        
        dvbt2SubStatus OBJECT IDENTIFIER ::= { dvbt2CoderSub 1 }

        
        dvbt2SubStateTable OBJECT-TYPE
            SYNTAX SEQUENCE OF Dvbt2SubStateEntry
            MAX-ACCESS not-accessible
            STATUS current
            DESCRIPTION
                "DVB-T2 Coder-Sub state information."
            ::= { dvbt2SubStatus 2 }

        
        dvbt2SubStateEntry OBJECT-TYPE
            SYNTAX Dvbt2SubStateEntry
            MAX-ACCESS not-accessible
            STATUS current
            DESCRIPTION
                "An entry in the dvbt2SubStateTable."
            AUGMENTS { dvbt2StateEntry }
            ::= { dvbt2SubStateTable 1 }

        
        Dvbt2SubStateEntry ::=
            SEQUENCE { 
                dvbt2SubStInputDetected
                    INTEGER,
                dvbt2SubStInputMatched
                    INTEGER,
                dvbt2SubStConfigurationMsg
                    SnmpAdminString
             }

        dvbt2SubStInputDetected OBJECT-TYPE
            SYNTAX INTEGER
                {
                off(1),
                unlocked(2),
                internal(3),
                mpeg(4),
                t2mi(5)
                }
            MAX-ACCESS read-only
            STATUS current
            DESCRIPTION
                "The current input state.
                internal(3) represents the test generator.
                unlocked(2), mpeg(4), t2mi(5): the status of the active input."
            ::= { dvbt2SubStateEntry 1 }

        
        dvbt2SubStInputMatched OBJECT-TYPE
            SYNTAX INTEGER
                {
                off(2),
                no(4),
                yes(5)
                }
            MAX-ACCESS read-only
            STATUS current
            DESCRIPTION
                "Result of comparison of dvbt2StInputDetected
                and dvbt2StInputRequired."
            ::= { dvbt2SubStateEntry 2 }

        
        dvbt2SubStConfigurationMsg OBJECT-TYPE
            SYNTAX SnmpAdminString (SIZE (0..160))
            MAX-ACCESS read-only
            STATUS current
            DESCRIPTION
                "Description."
            ::= { dvbt2SubStateEntry 7 }

        
        dvbt2SubSetup OBJECT IDENTIFIER ::= { dvbt2CoderSub 2 }

        
        dvbt2SubConfigurationTable OBJECT-TYPE
            SYNTAX SEQUENCE OF Dvbt2SubConfigurationEntry
            MAX-ACCESS not-accessible
            STATUS current
            DESCRIPTION
                "DVB-T2 Coder-Sub configuration."
            ::= { dvbt2SubSetup 1 }

        
        dvbt2SubConfigurationEntry OBJECT-TYPE
            SYNTAX Dvbt2SubConfigurationEntry
            MAX-ACCESS not-accessible
            STATUS current
            DESCRIPTION
                "An entry in the dvbt2SubConfigurationTable."
            AUGMENTS { dvbt2ConfigurationEntry }
            ::= { dvbt2SubConfigurationTable 1 }

        
        Dvbt2SubConfigurationEntry ::=
            SEQUENCE { 
                dvbt2SubConfigurationT2MiInterface
                    INTEGER,
                dvbt2SubConfigurationT2MiPID
                    Unsigned32,
                dvbt2SubConfigurationT2MiSID
                    Unsigned32
             }

        dvbt2SubConfigurationT2MiInterface OBJECT-TYPE
            SYNTAX INTEGER
                {
                on(1),
                off(2),
                composite(3)
                }
            MAX-ACCESS read-only
            STATUS current
            DESCRIPTION
                "on(1) - Uses the incoming T2-MI stream from a DVB-T2 gateway
                         to configure the Modulator.
                off(2) - Uses the incoming MPEG transport stream directly
                         as payload for single PLP."
            ::= { dvbt2SubConfigurationEntry 3 }

        
        dvbt2SubConfigurationT2MiPID OBJECT-TYPE
            SYNTAX Unsigned32 (0..8191)
            MAX-ACCESS read-write
            STATUS current
            DESCRIPTION
                "Only if dvbt2ConfigurationT2MiInterface is on(1):
                the packet ID of the T2-MI elementary stream."
            ::= { dvbt2SubConfigurationEntry 4 }

        
        dvbt2SubConfigurationT2MiSID OBJECT-TYPE
            SYNTAX Unsigned32 (0..7)
            MAX-ACCESS read-write
            STATUS current
            DESCRIPTION
                "Only if dvbt2FsT2Version is at least v131(5):
                "
            ::= { dvbt2SubConfigurationEntry 5 }

        
        dvbt2SubLocalizationTable OBJECT-TYPE
            SYNTAX SEQUENCE OF Dvbt2SubLocalizationEntry
            MAX-ACCESS not-accessible
            STATUS current
            DESCRIPTION
                "DVB-T2 Coder-Sub localization."
            ::= { dvbt2SubSetup 2 }

        
        dvbt2SubLocalizationEntry OBJECT-TYPE
            SYNTAX Dvbt2SubLocalizationEntry
            MAX-ACCESS not-accessible
            STATUS current
            DESCRIPTION
                "An entry in the dvbt2SubLocalizationTable."
            AUGMENTS { dvbt2ConfigurationEntry }
            ::= { dvbt2SubLocalizationTable 1 }

        
        Dvbt2SubLocalizationEntry ::=
            SEQUENCE { 
                dvbt2SubLocalizationTxIdentifier
                    Unsigned32,
                dvbt2SubLocalizationCellIdSource
                    Dvbt2CellIdSource,
                dvbt2SubLocalizationCellIdManual
                    Unsigned32,
                dvbt2SubLocalizationMisoGroupSource
                    INTEGER,
                dvbt2SubLocalizationMisoGroupManual
                    INTEGER,
                dvbt2SubLocalizationL1FrequencySource
                    Dvbt2L1FrequencySource,
                dvbt2SubLocalizationL1FrequencyManual
                    Unsigned32
             }

        dvbt2SubLocalizationTxIdentifier OBJECT-TYPE
            SYNTAX Unsigned32 (0..65535)
            MAX-ACCESS read-write
            STATUS current
            DESCRIPTION
                "Used to address a TV transmitter within a DVB-T2 network."
            ::= { dvbt2SubLocalizationEntry 3 }

        
        dvbt2SubLocalizationCellIdSource OBJECT-TYPE
            SYNTAX Dvbt2CellIdSource
            MAX-ACCESS read-write
            STATUS current
            DESCRIPTION
                "Source for the cell ID."
            ::= { dvbt2SubLocalizationEntry 4 }

        
        dvbt2SubLocalizationCellIdManual OBJECT-TYPE
            SYNTAX Unsigned32 (0..65535)
            MAX-ACCESS read-write
            STATUS current
            DESCRIPTION
                "The cell ID used when dvbt2LocalizationCellIdSource is manual(1).
                The cell ID can be changed without signal interruption."
            ::= { dvbt2SubLocalizationEntry 5 }

        
        dvbt2SubLocalizationMisoGroupSource OBJECT-TYPE
            SYNTAX INTEGER
                {
                off(1),
                manual(2),
                ia(3)
                }
            MAX-ACCESS read-write
            STATUS current
            DESCRIPTION
                "The MISO group can be configured either manually directly on the transmitter
                or automatically using the Individual Addressing (IA) data via the DVB_T2 gateway.
                The group can be switched at any time without signal interruption.
                
                manual(2) - from dvbt2LocalizationMisoGroupManual
                ia(3)     - from the individual addressing data
                            of the DVB-T2 gateway stream"
            ::= { dvbt2SubLocalizationEntry 6 }

        
        dvbt2SubLocalizationMisoGroupManual OBJECT-TYPE
            SYNTAX INTEGER
                {
                group1(4),
                group2(5)
                }
            MAX-ACCESS read-write
            STATUS current
            DESCRIPTION
                "The MISO group used when dvbt2LocalizationMisoGroupSource is manual(1).
                The MISO group can be changed without signal interruption."
            ::= { dvbt2SubLocalizationEntry 7 }

        
        dvbt2SubLocalizationL1FrequencySource OBJECT-TYPE
            SYNTAX Dvbt2L1FrequencySource
            MAX-ACCESS read-write
            STATUS current
            DESCRIPTION
                "See textual convention.
                
                If you select manual(1),
                the value is given with dvbt2LocalizationL1FrequencyManual."
            ::= { dvbt2SubLocalizationEntry 10 }

        
        dvbt2SubLocalizationL1FrequencyManual OBJECT-TYPE
            SYNTAX Unsigned32 (0..2000000000)
            UNITS "Hz"
            MAX-ACCESS read-write
            STATUS current
            DESCRIPTION
                "Presetting of L1 frequency shift."
            ::= { dvbt2SubLocalizationEntry 11 }

        
        dvbt2SubOutput OBJECT IDENTIFIER ::= { dvbt2CoderSub 3 }

        
        dvbt2SubOutLocalizationTable OBJECT-TYPE
            SYNTAX SEQUENCE OF Dvbt2SubOutLocalizationEntry
            MAX-ACCESS not-accessible
            STATUS current
            DESCRIPTION
                "DVB-T2 Coder-Sub localization
                as signalled from the DVB-T2 gateway."
            ::= { dvbt2SubOutput 2 }

        
        dvbt2SubOutLocalizationEntry OBJECT-TYPE
            SYNTAX Dvbt2SubOutLocalizationEntry
            MAX-ACCESS not-accessible
            STATUS current
            DESCRIPTION
                "Description."
            AUGMENTS { dvbt2ConfigurationEntry }
            ::= { dvbt2SubOutLocalizationTable 1 }

        
        Dvbt2SubOutLocalizationEntry ::=
            SEQUENCE { 
                dvbt2SubOutLocalizationCellIdSource
                    Dvbt2CellIdSource,
                dvbt2SubOutLocalizationCellId
                    Unsigned32,
                dvbt2SubOutLocalizationMisoGroupSource
                    INTEGER,
                dvbt2SubOutLocalizationMisoGroup
                    INTEGER,
                dvbt2SubOutLocalizationNetworkId
                    Unsigned32,
                dvbt2SubOutLocalizationSystemId
                    Unsigned32,
                dvbt2SubOutLocalizationL1Frequency
                    Unsigned32,
                dvbt2SubOutLocalizationPaprTrSource
                    INTEGER
             }

        dvbt2SubOutLocalizationCellIdSource OBJECT-TYPE
            SYNTAX Dvbt2CellIdSource
            MAX-ACCESS read-only
            STATUS current
            DESCRIPTION
                "See textual convention."
            ::= { dvbt2SubOutLocalizationEntry 1 }

        
        dvbt2SubOutLocalizationCellId OBJECT-TYPE
            SYNTAX Unsigned32
            MAX-ACCESS read-only
            STATUS current
            DESCRIPTION
                "The cell ID that is actually transmitted."
            ::= { dvbt2SubOutLocalizationEntry 3 }

        
        dvbt2SubOutLocalizationMisoGroupSource OBJECT-TYPE
            SYNTAX INTEGER
                {
                off(1),
                manual(2),
                ia(3)
                }
            MAX-ACCESS read-only
            STATUS current
            DESCRIPTION
                "Source for the MISO group:
                manual(2) - from dvbt2LocalizationMisoGroupManual
                ia(3)     - from the individual addressing data
                            of the DVB-T2 gateway stream"
            ::= { dvbt2SubOutLocalizationEntry 4 }

        
        dvbt2SubOutLocalizationMisoGroup OBJECT-TYPE
            SYNTAX INTEGER
                {
                unused(3),
                group1(4),
                group2(5)
                }
            MAX-ACCESS read-only
            STATUS current
            DESCRIPTION
                "The actual MISO group for the transmitter.
                In a MISO system the two transmitters have to be assigned
                different groups.
                In a SFN system several transmitters may belong to one group."
            ::= { dvbt2SubOutLocalizationEntry 5 }

        
        dvbt2SubOutLocalizationNetworkId OBJECT-TYPE
            SYNTAX Unsigned32
            MAX-ACCESS read-only
            STATUS current
            DESCRIPTION
                "The actual network ID for the transmitter."
            ::= { dvbt2SubOutLocalizationEntry 6 }

        
        dvbt2SubOutLocalizationSystemId OBJECT-TYPE
            SYNTAX Unsigned32
            MAX-ACCESS read-only
            STATUS current
            DESCRIPTION
                "The actual system ID for the transmitter."
            ::= { dvbt2SubOutLocalizationEntry 7 }

        
        dvbt2SubOutLocalizationL1Frequency OBJECT-TYPE
            SYNTAX Unsigned32
            UNITS "Hz"
            MAX-ACCESS read-only
            STATUS current
            DESCRIPTION
                "Currently used L1 frequency with index 0."
            ::= { dvbt2SubOutLocalizationEntry 9 }

        
        dvbt2SubOutLocalizationPaprTrSource OBJECT-TYPE
            SYNTAX INTEGER
                {
                off(1),
                manual(2),
                ia(3),
                supported(4)
                }
            MAX-ACCESS read-write
            STATUS current
            DESCRIPTION
                "Description."
            ::= { dvbt2SubOutLocalizationEntry 12 }

        
        dvbt2SubOutChannelTable OBJECT-TYPE
            SYNTAX SEQUENCE OF Dvbt2SubOutChannelEntry
            MAX-ACCESS not-accessible
            STATUS current
            DESCRIPTION
                "DVB-T2 Coder-Sub channel parameters
                as signalled from the DVB-T2 gateway."
            ::= { dvbt2SubOutput 4 }

        
        dvbt2SubOutChannelEntry OBJECT-TYPE
            SYNTAX Dvbt2SubOutChannelEntry
            MAX-ACCESS not-accessible
            STATUS current
            DESCRIPTION
                "Description."
            AUGMENTS { dvbt2ConfigurationEntry }
            ::= { dvbt2SubOutChannelTable 1 }

        
        Dvbt2SubOutChannelEntry ::=
            SEQUENCE { 
                dvbt2SubOutChnTransmissionSystem
                    Dvbt2TransmissionSystem,
                dvbt2SubOutChnBandwidth
                    Dvbt2ChannelBandwidth,
                dvbt2SubOutChnFFT
                    Dvbt2FftSize,
                dvbt2SubOutChnFftExtended
                    Dvbt2OnOff,
                dvbt2SubOutChnGuardInterval
                    Dvbt2GuardInterval,
                dvbt2SubOutChnPilotPattern
                    Dvbt2PilotPattern,
                dvbt2SubOutChnPaprReduction
                    Dvbt2PaprReduction,
                dvbt2SubOutChnT2Profile
                    INTEGER
             }

        dvbt2SubOutChnTransmissionSystem OBJECT-TYPE
            SYNTAX Dvbt2TransmissionSystem
            MAX-ACCESS read-only
            STATUS current
            DESCRIPTION
                "see textual convention"
            ::= { dvbt2SubOutChannelEntry 3 }

        
        dvbt2SubOutChnBandwidth OBJECT-TYPE
            SYNTAX Dvbt2ChannelBandwidth
            MAX-ACCESS read-only
            STATUS current
            DESCRIPTION
                "The channel bandwidth as signalled by the DVB-T2 gateway."
            ::= { dvbt2SubOutChannelEntry 4 }

        
        dvbt2SubOutChnFFT OBJECT-TYPE
            SYNTAX Dvbt2FftSize
            MAX-ACCESS read-only
            STATUS current
            DESCRIPTION
                "see textual convention"
            ::= { dvbt2SubOutChannelEntry 5 }

        
        dvbt2SubOutChnFftExtended OBJECT-TYPE
            SYNTAX Dvbt2OnOff
            MAX-ACCESS read-only
            STATUS current
            DESCRIPTION
                "When this field is on(1), the extended carrier mode is used.
                If this field is off(2), the normal carrier mode is used.
                Only for 8K, 16K or 32K FFT size."
            ::= { dvbt2SubOutChannelEntry 6 }

        
        dvbt2SubOutChnGuardInterval OBJECT-TYPE
            SYNTAX Dvbt2GuardInterval
            MAX-ACCESS read-only
            STATUS current
            DESCRIPTION
                "see textual convention"
            ::= { dvbt2SubOutChannelEntry 7 }

        
        dvbt2SubOutChnPilotPattern OBJECT-TYPE
            SYNTAX Dvbt2PilotPattern
            MAX-ACCESS read-only
            STATUS current
            DESCRIPTION
                "see textual convention"
            ::= { dvbt2SubOutChannelEntry 8 }

        
        dvbt2SubOutChnPaprReduction OBJECT-TYPE
            SYNTAX Dvbt2PaprReduction
            MAX-ACCESS read-only
            STATUS current
            DESCRIPTION
                "see textual convention"
            ::= { dvbt2SubOutChannelEntry 9 }

        
        dvbt2SubOutChnT2Profile OBJECT-TYPE
            SYNTAX INTEGER
                {
                undefined(1),
                base(3),
                baseLite(4),
                lite(5)
                }
            MAX-ACCESS read-only
            STATUS current
            DESCRIPTION
                "The T2-profile used. The standard profile is T2-Base,
                while T2-Lite has been introduced in T2 version 1.3.1.
                T2-Lite is intended for mobile applications.
                The T2-Base-Lite option is the intersection between T2-Base and T2-Lite,
                i.e. a signal that is valid for both T2-Base and T2-Lite profiles.
                The T2-Base-Lite profile will be signalled as a normal T2-Base signal,
                but with the T2_BASE_LITE flag set in the L1-Pre signaling."
            ::= { dvbt2SubOutChannelEntry 14 }

        
        dvbt2SubOutFrameStructureTable OBJECT-TYPE
            SYNTAX SEQUENCE OF Dvbt2SubOutFrameStructureEntry
            MAX-ACCESS not-accessible
            STATUS current
            DESCRIPTION
                "DVB-T2 Coder-Sub frame structure
                as signalled from the DVB-T2 gateway."
            ::= { dvbt2SubOutput 5 }

        
        dvbt2SubOutFrameStructureEntry OBJECT-TYPE
            SYNTAX Dvbt2SubOutFrameStructureEntry
            MAX-ACCESS not-accessible
            STATUS current
            DESCRIPTION
                "An entry in the dvbt2SubOutFrameStructureTable. "
            AUGMENTS { dvbt2ConfigurationEntry }
            ::= { dvbt2SubOutFrameStructureTable 1 }

        
        Dvbt2SubOutFrameStructureEntry ::=
            SEQUENCE { 
                dvbt2SubOutFsDataSymbolsPerT2Frame
                    Unsigned32,
                dvbt2SubOutFsT2FramesPerSuperFrame
                    Unsigned32,
                dvbt2SubOutFsT2Version
                    Dvbt2T2Version,
                dvbt2SubOutFsNumOfPLP
                    Unsigned32,
                dvbt2SubOutFsNumOfAux
                    Unsigned32
             }

        dvbt2SubOutFsDataSymbolsPerT2Frame OBJECT-TYPE
            SYNTAX Unsigned32
            MAX-ACCESS read-only
            STATUS current
            DESCRIPTION
                "The total number of symbols in a frame (excluding P1).
                
                If a T2-MI interface is used, this value is read-only.
                In this case it is specified by the DVB-T2 gateway."
            ::= { dvbt2SubOutFrameStructureEntry 3 }

        
        dvbt2SubOutFsT2FramesPerSuperFrame OBJECT-TYPE
            SYNTAX Unsigned32
            MAX-ACCESS read-only
            STATUS current
            DESCRIPTION
                "The number of T2-frames in a super-frame is a configurable parameter.
                
                If a T2-MI interface is used, this value is read-only.
                In this case it is specified by the DVB-T2 gateway."
            ::= { dvbt2SubOutFrameStructureEntry 4 }

        
        dvbt2SubOutFsT2Version OBJECT-TYPE
            SYNTAX Dvbt2T2Version
            MAX-ACCESS read-only
            STATUS current
            DESCRIPTION
                "If no T2-MI interface is used only version 1.1.1 is supported."
            ::= { dvbt2SubOutFrameStructureEntry 5 }

        
        dvbt2SubOutFsNumOfPLP OBJECT-TYPE
            SYNTAX Unsigned32
            MAX-ACCESS read-only
            STATUS current
            DESCRIPTION
                "The number of PLPs carried within the super-frame."
            ::= { dvbt2SubOutFrameStructureEntry 7 }

        
        dvbt2SubOutFsNumOfAux OBJECT-TYPE
            SYNTAX Unsigned32
            MAX-ACCESS read-only
            STATUS current
            DESCRIPTION
                "number of auxiliary streams"
            ::= { dvbt2SubOutFrameStructureEntry 8 }

        
        dvbt2SubOutL1Table OBJECT-TYPE
            SYNTAX SEQUENCE OF Dvbt2SubOutL1Entry
            MAX-ACCESS not-accessible
            STATUS current
            DESCRIPTION
                "DVB-T2 Coder-Sub layer 1 parameters
                as signalled from the DVB-T2 gateway."
            ::= { dvbt2SubOutput 6 }

        
        dvbt2SubOutL1Entry OBJECT-TYPE
            SYNTAX Dvbt2SubOutL1Entry
            MAX-ACCESS not-accessible
            STATUS current
            DESCRIPTION
                "An entry in the dvbt2SubOutL1Table."
            AUGMENTS { dvbt2ConfigurationEntry }
            ::= { dvbt2SubOutL1Table 1 }

        
        Dvbt2SubOutL1Entry ::=
            SEQUENCE { 
                dvbt2SubOutL1Modulation
                    Dvbt2Layer1Modulation,
                dvbt2SubOutL1CodeRate
                    Dvbt2Layer1CodeRate,
                dvbt2SubOutL1Repetition
                    Dvbt2OnOff,
                dvbt2SubOutL1PostScrambled
                    Dvbt2OnOff
             }

        dvbt2SubOutL1Modulation OBJECT-TYPE
            SYNTAX Dvbt2Layer1Modulation
            MAX-ACCESS read-only
            STATUS current
            DESCRIPTION
                "The constellation of the L1-post signalling data block."
            ::= { dvbt2SubOutL1Entry 3 }

        
        dvbt2SubOutL1CodeRate OBJECT-TYPE
            SYNTAX Dvbt2Layer1CodeRate
            MAX-ACCESS read-only
            STATUS current
            DESCRIPTION
                "The coding of the L1-post signalling data block."
            ::= { dvbt2SubOutL1Entry 4 }

        
        dvbt2SubOutL1Repetition OBJECT-TYPE
            SYNTAX Dvbt2OnOff
            MAX-ACCESS read-only
            STATUS current
            DESCRIPTION
                "Repetition of L1-post dynamic data."
            ::= { dvbt2SubOutL1Entry 6 }

        
        dvbt2SubOutL1PostScrambled OBJECT-TYPE
            SYNTAX Dvbt2OnOff
            MAX-ACCESS read-only
            STATUS current
            DESCRIPTION
                "Shows whether signalling of L1-post is scrambled."
            ::= { dvbt2SubOutL1Entry 7 }

        
        dvbt2SubOutPlpTable OBJECT-TYPE
            SYNTAX SEQUENCE OF Dvbt2SubOutPlpEntry
            MAX-ACCESS not-accessible
            STATUS current
            DESCRIPTION
                "DVB-T2 Coder-Sub PLP parameters
                as signalled from the DVB-T2 gateway."
            ::= { dvbt2SubOutput 7 }

        
        dvbt2SubOutPlpEntry OBJECT-TYPE
            SYNTAX Dvbt2SubOutPlpEntry
            MAX-ACCESS not-accessible
            STATUS current
            DESCRIPTION
                "An entry in the dvbt2SubOutPlpTable."
            INDEX { dvbt2ConfigurationTxIdx, dvbt2ConfigurationExcIdx, dvbt2SubOutPlpIdx }
            ::= { dvbt2SubOutPlpTable 1 }

        
        Dvbt2SubOutPlpEntry ::=
            SEQUENCE { 
                dvbt2SubOutPlpIdx
                    Unsigned32,
                dvbt2SubOutPlpID
                    Unsigned32,
                dvbt2SubOutPlpGroupID
                    Unsigned32,
                dvbt2SubOutPlpType
                    Dvbt2PlpType,
                dvbt2SubOutPlpPayloadType
                    INTEGER,
                dvbt2SubOutPlpConstellation
                    Dvbt2Modulation,
                dvbt2SubOutPlpRotation
                    Dvbt2OnOff,
                dvbt2SubOutPlpCodeRate
                    Dvbt2CodeRate,
                dvbt2SubOutPlpFEC
                    Dvbt2FEC,
                dvbt2SubOutPlpTimeInterleaverType
                    Dvbt2TimeInterleaverType,
                dvbt2SubOutPlpTimeInterleaverLength
                    Unsigned32,
                dvbt2SubOutPlpBasebandMode
                    Dvbt2BasebandMode
             }

        dvbt2SubOutPlpIdx OBJECT-TYPE
            SYNTAX Unsigned32 (1..8)
            MAX-ACCESS not-accessible
            STATUS current
            DESCRIPTION
                "The PLP number.
                This is a helper column and therefore not-accessible."
            ::= { dvbt2SubOutPlpEntry 2 }

        
        dvbt2SubOutPlpID OBJECT-TYPE
            SYNTAX Unsigned32
            MAX-ACCESS read-only
            STATUS current
            DESCRIPTION
                "uniquely identifies a PLP within a T2 system"
            ::= { dvbt2SubOutPlpEntry 3 }

        
        dvbt2SubOutPlpGroupID OBJECT-TYPE
            SYNTAX Unsigned32
            MAX-ACCESS read-only
            STATUS current
            DESCRIPTION
                "identifies with which PLP group within the T2 system
                the current PLP is associated. This can be used by a
                receiver to link the data PLP to its associated common PLP,
                which will have the same PLP Group ID.
                "
            ::= { dvbt2SubOutPlpEntry 4 }

        
        dvbt2SubOutPlpType OBJECT-TYPE
            SYNTAX Dvbt2PlpType
            MAX-ACCESS read-only
            STATUS current
            DESCRIPTION
                "Indicates the set Physical Layer Pipe type."
            ::= { dvbt2SubOutPlpEntry 5 }

        
        dvbt2SubOutPlpPayloadType OBJECT-TYPE
            SYNTAX INTEGER
                {
                reserved(2),
                gfps(3),
                gcs(4),
                gse(5),
                ts(6)
                }
            MAX-ACCESS read-only
            STATUS current
            DESCRIPTION
                "Each input PLP may take one of the following formats:
                gfps(3) - Generic Fixed-length Packetized Stream
                          This form is retained for compatibility with DVB-S2,
                          but it is expected that GSE would now be used instead.
                gcs(4)  - Generic Continuous Stream
                          A variable length packet stream where the modulator
                          is not aware of the packet boundaries.
                gse(5)  - Generic Encapsulated Stream
                ts(6)   - Transport Stream"
            ::= { dvbt2SubOutPlpEntry 6 }

        
        dvbt2SubOutPlpConstellation OBJECT-TYPE
            SYNTAX Dvbt2Modulation
            MAX-ACCESS read-only
            STATUS current
            DESCRIPTION
                "Indicates the set modulation mode. 
                QPSK is extremely fail-safe, but has only a low data rate. 
                256QAM can transmit very high data rates and is 
                recommended if few faults are expected on the 
                transmission link. 
                "
            ::= { dvbt2SubOutPlpEntry 7 }

        
        dvbt2SubOutPlpRotation OBJECT-TYPE
            SYNTAX Dvbt2OnOff
            MAX-ACCESS read-only
            STATUS current
            DESCRIPTION
                "Constellation rotation."
            ::= { dvbt2SubOutPlpEntry 8 }

        
        dvbt2SubOutPlpCodeRate OBJECT-TYPE
            SYNTAX Dvbt2CodeRate
            MAX-ACCESS read-only
            STATUS current
            DESCRIPTION
                "Indicates the set code rate. The code rate is used to set the ratio 
                of information data to <error correction values + information data>. 
                1/2 provides the greatest error correction and the lowest data 
                transfer rate; 
                5/6 provides the lowest error correction and the greatest data 
                transfer rate.
                "
            ::= { dvbt2SubOutPlpEntry 9 }

        
        dvbt2SubOutPlpFEC OBJECT-TYPE
            SYNTAX Dvbt2FEC
            MAX-ACCESS read-only
            STATUS current
            DESCRIPTION
                "Indicates the set error correction algorithm (FEC).  If a T2-MI interface 
                is used, this value is fixed by the DVB-T2 gateway.
                "
            ::= { dvbt2SubOutPlpEntry 10 }

        
        dvbt2SubOutPlpTimeInterleaverType OBJECT-TYPE
            SYNTAX Dvbt2TimeInterleaverType
            MAX-ACCESS read-only
            STATUS current
            DESCRIPTION
                "single(1) - Maps each interleaving frame directly  to a T2 frame.
                multi(2)  - Maps each interleaving frame to more than one T2 frame."
            ::= { dvbt2SubOutPlpEntry 12 }

        
        dvbt2SubOutPlpTimeInterleaverLength OBJECT-TYPE
            SYNTAX Unsigned32
            MAX-ACCESS read-only
            STATUS current
            DESCRIPTION
                "Defines the number of time interleaver blocks (TIB)
                within the time interleaving frame."
            ::= { dvbt2SubOutPlpEntry 13 }

        
        dvbt2SubOutPlpBasebandMode OBJECT-TYPE
            SYNTAX Dvbt2BasebandMode
            MAX-ACCESS read-only
            STATUS current
            DESCRIPTION
                "see textual convention"
            ::= { dvbt2SubOutPlpEntry 14 }

        
        dvbt2SubOutPaprTrTable OBJECT-TYPE
            SYNTAX SEQUENCE OF Dvbt2SubOutPaprTrEntry
            MAX-ACCESS not-accessible
            STATUS current
            DESCRIPTION
                "Coder-Sub PAPR (Peak to Average Power Ratio) reduction using tone reservation parameters."
            ::= { dvbt2SubOutput 8 }

        
        dvbt2SubOutPaprTrEntry OBJECT-TYPE
            SYNTAX Dvbt2SubOutPaprTrEntry
            MAX-ACCESS not-accessible
            STATUS current
            DESCRIPTION
                "An entry in the dvbt2SubOutPaprTrTable."
            AUGMENTS { dvbt2ConfigurationEntry }
            ::= { dvbt2SubOutPaprTrTable 1 }

        
        Dvbt2SubOutPaprTrEntry ::=
            SEQUENCE { 
                dvbt2SubOutPaprTrIterations
                    Unsigned32,
                dvbt2SubOutPaprTrClippingThreshold
                    Unsigned32,
                dvbt2SubOutPaprTrIterationsSupported
                    Unsigned32,
                dvbt2SubOutPaprTrIterationsIA
                    Unsigned32,
                dvbt2SubOutPaprTrIterationsReduced
                    TruthValue,
                dvbt2SubOutPaprTrIterationsActive
                    Unsigned32
             }

        dvbt2SubOutPaprTrIterations OBJECT-TYPE
            SYNTAX Unsigned32
            MAX-ACCESS read-only
            STATUS current
            DESCRIPTION
                "Indicates the maximum number of tone reservation repetitions 
                that are supported by the currently selected Bandwidth, FFT 
                and Guard Interval settings.
                "
            ::= { dvbt2SubOutPaprTrEntry 1 }

        
        dvbt2SubOutPaprTrClippingThreshold OBJECT-TYPE
            SYNTAX Unsigned32
            MAX-ACCESS read-only
            STATUS current
            DESCRIPTION
                "Indicates the limit up to which the PAPR-TR algorithm operates. 
                The displayed value divided by 100 roughly corresponds to the 
                desired crest factor in dB.
                "
            ::= { dvbt2SubOutPaprTrEntry 2 }

        
        dvbt2SubOutPaprTrIterationsSupported OBJECT-TYPE
            SYNTAX Unsigned32
            MAX-ACCESS read-only
            STATUS current
            DESCRIPTION
                "Maximum number of iterations of tone reservation that are supported
                for the adjusted bandwidth, FFT and guard interval."
            ::= { dvbt2SubOutPaprTrEntry 3 }

        
        dvbt2SubOutPaprTrIterationsIA OBJECT-TYPE
            SYNTAX Unsigned32
            MAX-ACCESS read-only
            STATUS current
            DESCRIPTION
                "Description."
            ::= { dvbt2SubOutPaprTrEntry 4 }

        
        dvbt2SubOutPaprTrIterationsReduced OBJECT-TYPE
            SYNTAX TruthValue
            MAX-ACCESS read-only
            STATUS current
            DESCRIPTION
                "The number of iterations signalled by IA is too high.
                The number of active iterations is reduced to the number of supported iterations."
            ::= { dvbt2SubOutPaprTrEntry 5 }

        
        dvbt2SubOutPaprTrIterationsActive OBJECT-TYPE
            SYNTAX Unsigned32
            MAX-ACCESS read-only
            STATUS current
            DESCRIPTION
                "Number of iterations of tone reservations per symbol."
            ::= { dvbt2SubOutPaprTrEntry 6 }

        
        dvbt2SubOutFefTable OBJECT-TYPE
            SYNTAX SEQUENCE OF Dvbt2SubOutFefEntry
            MAX-ACCESS not-accessible
            STATUS current
            DESCRIPTION
                "Coder-Sub FEF (future extension frame) values."
            ::= { dvbt2SubOutput 9 }

        
        dvbt2SubOutFefEntry OBJECT-TYPE
            SYNTAX Dvbt2SubOutFefEntry
            MAX-ACCESS not-accessible
            STATUS current
            DESCRIPTION
                "An entry in the dvbt2SubOutFefTable"
            AUGMENTS { dvbt2ConfigurationEntry }
            ::= { dvbt2SubOutFefTable 1 }

        
        Dvbt2SubOutFefEntry ::=
            SEQUENCE { 
                dvbt2SubOutFefOn
                    Dvbt2OnOff,
                dvbt2SubOutFefType
                    Unsigned32,
                dvbt2SubOutFefLength
                    Unsigned32,
                dvbt2SubOutFefInterval
                    Unsigned32
             }

        dvbt2SubOutFefOn OBJECT-TYPE
            SYNTAX Dvbt2OnOff
            MAX-ACCESS read-only
            STATUS current
            DESCRIPTION
                "Indicates whether future extension frames are used."
            ::= { dvbt2SubOutFefEntry 1 }

        
        dvbt2SubOutFefType OBJECT-TYPE
            SYNTAX Unsigned32
            MAX-ACCESS read-only
            STATUS current
            DESCRIPTION
                "Indicates the type of the associated FEF part as a digit."
            ::= { dvbt2SubOutFefEntry 2 }

        
        dvbt2SubOutFefLength OBJECT-TYPE
            SYNTAX Unsigned32
            MAX-ACCESS read-only
            STATUS current
            DESCRIPTION
                "Indicates the length of the used FEF part as the number of periods T from the 
                beginning of the P1 symbol of the FEF part to the beginning of the P1 symbol 
                of the next T2 frame."
            ::= { dvbt2SubOutFefEntry 3 }

        
        dvbt2SubOutFefInterval OBJECT-TYPE
            SYNTAX Unsigned32
            MAX-ACCESS read-only
            STATUS current
            DESCRIPTION
                "Indicates the number of T2-frames between two FEF parts."
            ::= { dvbt2SubOutFefEntry 4 }

        
        rsXx9Dvbt2Conformance OBJECT IDENTIFIER ::= { rsXx9DvbT2 2 }

        
        rsXx9Dvbt2Compliances OBJECT IDENTIFIER ::= { rsXx9Dvbt2Conformance 1 }

        
        dvbt2BasicCompliance MODULE-COMPLIANCE
            STATUS current
            DESCRIPTION 
                "The compliance statement for XX9000 DVB-T2 exciters."
            MODULE -- this module
                MANDATORY-GROUPS { dvbt2ObjBasic, dvbt2NotifyBasic }
            ::= { rsXx9Dvbt2Compliances 1 }

        
        rsXx9Dvbt2Groups OBJECT IDENTIFIER ::= { rsXx9Dvbt2Conformance 2 }

        
        dvbt2ObjBasic OBJECT-GROUP
            OBJECTS { dvbt2StatusNotificationName, dvbt2StatusNotificationMask, dvbt2StatusNotificationPriority, dvbt2StatusNotificationState, dvbt2ConfigurationT2MiInterface, 
                dvbt2ConfigurationT2MiPID, dvbt2LocalizationTxIdentifier, dvbt2LocalizationCellIdSource, dvbt2LocalizationCellIdManual, dvbt2LocalizationMisoGroupSource, 
                dvbt2LocalizationMisoGroupManual, dvbt2LocalizationNetworkIdManual, dvbt2LocalizationSystemIdManual, dvbt2IaTimeOffset, dvbt2IaTimeOffsetSource, 
                dvbt2IaFrequencyOffset, dvbt2IaFrequencyOffsetSource, dvbt2IaCellID, dvbt2IaCellIdSource, dvbt2FsDataSymbolsPerT2Frame, 
                dvbt2FsT2FramesPerSuperFrame, dvbt2L1Modulation, dvbt2L1CodeRate, dvbt2L1FEC, dvbt2L1Repetition, 
                dvbt2StInputDetected, dvbt2StInputMatched, dvbt2StInputRequired, dvbt2Plp1ID, dvbt2Plp1GroupID, 
                dvbt2Plp1Type, dvbt2Plp1Constellation, dvbt2Plp1Rotation, dvbt2Plp1CodeRate, dvbt2Plp1FEC, 
                dvbt2Plp1TimeInterleaverType, dvbt2Plp1TimeInterleaverLength, dvbt2Plp1BasebandMode, dvbt2OutPlpBasebandMode, dvbt2OutPlpTimeInterleaverLength, 
                dvbt2OutPlpTimeInterleaverType, dvbt2OutPlpFEC, dvbt2OutPlpCodeRate, dvbt2OutPlpRotation, dvbt2OutPlpConstellation, 
                dvbt2OutPlpPayloadType, dvbt2OutPlpType, dvbt2OutPlpGroupID, dvbt2OutPlpID, dvbt2OutL1Repetition, 
                dvbt2OutL1FEC, dvbt2OutL1CodeRate, dvbt2OutL1Modulation, dvbt2LocalizationL1FrequencyManual, dvbt2OutLocalizationCellId, 
                dvbt2OutLocalizationMisoGroup, dvbt2OutLocalizationNetworkId, dvbt2OutLocalizationSystemId, dvbt2OutLocalizationL1Frequency, dvbt2OutFsT2Version, 
                dvbt2LocalizationL1FrequencySource, dvbt2OutLocalizationMisoGroupSource, dvbt2OutLocalizationCellIdSource, dvbt2OutLocalizationL1FrequencySource, dvbt2OutFsT2FramesPerSuperFrame, 
                dvbt2OutLocalizationTxDelayOffsetSource, dvbt2LocalizationTxDelayOffsetSource, dvbt2FsT2Version, dvbt2OutLocalizationTxDelayOffset, dvbt2OutPlpFrameInterval, 
                dvbt2OutPlpBasebandPayloadPadding, dvbt2OutPlpNullPacketDeletion, dvbt2OutPlpCmType, dvbt2OutPlpInBandFlag, dvbt2OutPlpInBandASig, 
                dvbt2OutPlpInBandBSig, dvbt2ConfigurationT2MiSID, dvbt2OutChnT2BaseLite, dvbt2OutChnInputStreamTypes, dvbt2OutChnRegenerationFlag, 
                dvbt2OutFsSubSlicesPerFrame, dvbt2OutFsNumOfPLP, dvbt2OutFsNumOfAux, dvbt2OutL1PostScrambled, dvbt2OutL1PostExtension, 
                dvbt2OutChnPreamble, dvbt2OutPlpNumOfOtherPlpInBand, dvbt2OutPaprTrIterations, dvbt2OutPaprTrClippingThreshold, dvbt2OutFefOn, 
                dvbt2OutFefType, dvbt2OutFefLength, dvbt2OutFefInterval, dvbt2OutChnT2Profile, dvbt2TestMode, 
                dvbt2OutPaprTrIterationsSupported, dvbt2OutPaprTrIterationsIA, dvbt2OutPaprTrIterationsReduced, dvbt2OutPaprTrIterationsActive, dvbt2ConfigurationT2ConfigAdaption, 
                dvbt2StConfigAdaptionState, dvbt2ConfigurationT2MiDejitterBufDelay, dvbt2OutLocalizationPaprTrSource, dvbt2LocalizationPaprTrSource, dvbt2StResidualDelay, 
                dvbt2StDejitterBufDelay, dvbt2StConfigurationMsg, dvbt2OutFsDataSymbolsPerT2Frame, dvbt2ChnTransmissionSystem, dvbt2ChnBandwidth, 
                dvbt2ChnFFT, dvbt2ChnFftExtended, dvbt2ChnGuardInterval, dvbt2ChnPilotPattern, dvbt2ChnPaprReduction, 
                dvbt2OutChnTransmissionSystem, dvbt2OutChnBandwidth, dvbt2OutChnFFT, dvbt2OutChnFftExtended, dvbt2OutChnGuardInterval, 
                dvbt2OutChnPilotPattern, dvbt2OutChnPaprReduction }
            STATUS current
            DESCRIPTION 
                "Basic objects group."
            ::= { rsXx9Dvbt2Groups 1 }

        
        dvbt2NotifyBasic NOTIFICATION-GROUP
            NOTIFICATIONS { dvbt2L1State, dvbt2IaState, dvbt2ConfigurationValid, dvbt2ConfigurationSupported, dvbt2ConfigurationMatched, 
                dvbt2EncoderSummary, dvbt2Test, dvbt2SupportedPlps, dvbt2SupportedTrIterations }
            STATUS current
            DESCRIPTION 
                "Basic notifications group."
            ::= { rsXx9Dvbt2Groups 2 }

        
        dvbt2ObjObsoleted OBJECT-GROUP
            OBJECTS { dvbt2TestGeneration, dvbt2OutPlpFecBlocks, dvbt2OutPlpISSY }
            STATUS obsolete
            DESCRIPTION 
                "Obsoleted objects group."
            ::= { rsXx9Dvbt2Groups 3 }

        
        dvbt2ObjSubBasic OBJECT-GROUP
            OBJECTS { dvbt2SubStInputDetected, dvbt2SubStInputMatched, dvbt2SubStConfigurationMsg, dvbt2SubConfigurationT2MiInterface, dvbt2SubConfigurationT2MiPID, 
                dvbt2SubConfigurationT2MiSID, dvbt2SubLocalizationTxIdentifier, dvbt2SubLocalizationCellIdSource, dvbt2SubLocalizationCellIdManual, dvbt2SubLocalizationMisoGroupSource, 
                dvbt2SubLocalizationMisoGroupManual, dvbt2SubLocalizationL1FrequencySource, dvbt2SubLocalizationL1FrequencyManual, dvbt2SubOutLocalizationCellIdSource, dvbt2SubOutLocalizationCellId, 
                dvbt2SubOutLocalizationMisoGroupSource, dvbt2SubOutLocalizationMisoGroup, dvbt2SubOutLocalizationNetworkId, dvbt2SubOutLocalizationSystemId, dvbt2SubOutLocalizationL1Frequency, 
                dvbt2SubOutLocalizationPaprTrSource, dvbt2SubOutChnTransmissionSystem, dvbt2SubOutChnBandwidth, dvbt2SubOutChnFFT, dvbt2SubOutChnFftExtended, 
                dvbt2SubOutChnGuardInterval, dvbt2SubOutChnPilotPattern, dvbt2SubOutChnPaprReduction, dvbt2SubOutChnT2Profile, dvbt2SubOutFsDataSymbolsPerT2Frame, 
                dvbt2SubOutFsT2FramesPerSuperFrame, dvbt2SubOutFsT2Version, dvbt2SubOutFsNumOfPLP, dvbt2SubOutFsNumOfAux, dvbt2SubOutL1Modulation, 
                dvbt2SubOutL1CodeRate, dvbt2SubOutL1Repetition, dvbt2SubOutL1PostScrambled, dvbt2SubOutPlpID, dvbt2SubOutPlpGroupID, 
                dvbt2SubOutPlpType, dvbt2SubOutPlpPayloadType, dvbt2SubOutPlpConstellation, dvbt2SubOutPlpRotation, dvbt2SubOutPlpCodeRate, 
                dvbt2SubOutPlpFEC, dvbt2SubOutPlpTimeInterleaverType, dvbt2SubOutPlpTimeInterleaverLength, dvbt2SubOutPlpBasebandMode, dvbt2SubOutPaprTrIterations, 
                dvbt2SubOutPaprTrClippingThreshold, dvbt2SubOutPaprTrIterationsSupported, dvbt2SubOutPaprTrIterationsIA, dvbt2SubOutPaprTrIterationsReduced, dvbt2SubOutPaprTrIterationsActive, 
                dvbt2SubOutFefOn, dvbt2SubOutFefType, dvbt2SubOutFefLength, dvbt2SubOutFefInterval }
            STATUS current
            DESCRIPTION 
                "Description."
            ::= { rsXx9Dvbt2Groups 4 }

        
        dvbt2NotifySubBasic NOTIFICATION-GROUP
            NOTIFICATIONS { dvbt2CompositeSummary, dvbt2CompositeProfiles, dvbt2CompositeFrameLength, dvbt2SubIaState, dvbt2SubConfigurationValid, 
                dvbt2SubConfigurationSupported, dvbt2SubConfigurationMatched }
            STATUS current
            DESCRIPTION 
                "Description."
            ::= { rsXx9Dvbt2Groups 5 }

        
        dvbt2NotifObsoleted NOTIFICATION-GROUP
            NOTIFICATIONS { dvbt2T2MiTimeInterleaverBuffer }
            STATUS obsolete
            DESCRIPTION 
                "Obsoleted notifications group."
            ::= { rsXx9Dvbt2Groups 6 }

        
    
    END

--
-- RS-XX9-DVBT2-MIB.mi2
--
