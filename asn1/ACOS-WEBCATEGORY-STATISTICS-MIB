ACOS-WEBCATEGORY-STATISTICS-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		webCategoryStatisticsModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "webCategoryStatisticsModule OID for ACOS"
				::=  {  acosSchema 280 }

statistics		 OBJECT IDENTIFIER ::= { webCategoryStatisticsModule 1}

statisticsStatsTable OBJECT-TYPE
	 SYNTAX SEQUENCE OF StatisticsStatsEntry
	 MAX-ACCESS not-accessible
	 STATUS current
	 DESCRIPTION
	 "Statistics from object 'web-category.statistics'"
	::= {statistics 1}

statisticsStatsEntry OBJECT-TYPE
	SYNTAX StatisticsStatsEntry
	MAX-ACCESS not-accessible
	STATUS current
	DESCRIPTION
		"The statisticsStats stats entry"
	INDEX {
		statisticsStatsSlotId
	}
	::= { statisticsStatsTable 1 }

StatisticsStatsEntry ::=
	SEQUENCE {
		statisticsStatsSlotId Integer32,
		statisticsStatsDbLookup	 CounterBasedGauge64,
		statisticsStatsCloudCacheLookup	 CounterBasedGauge64,
		statisticsStatsCloudLookup	 CounterBasedGauge64,
		statisticsStatsRtuLookup	 CounterBasedGauge64,
		statisticsStatsLookupLatency	 CounterBasedGauge64,
		statisticsStatsDbMem	 CounterBasedGauge64,
		statisticsStatsRtuCacheMem	 CounterBasedGauge64,
		statisticsStatsLookupCacheMem	 CounterBasedGauge64
	}

statisticsStatsSlotId OBJECT-TYPE
	 SYNTAX Integer32
	 MAX-ACCESS read-only
	 STATUS current
	 DESCRIPTION
		 ""
	::= { statisticsStatsEntry 1 }

statisticsStatsDbLookup OBJECT-TYPE
	 SYNTAX Integer32
	 MAX-ACCESS read-only
	 STATUS current
	 DESCRIPTION
		 "db-lookup"
	::= { statisticsStatsEntry 2 }

statisticsStatsCloudCacheLookup OBJECT-TYPE
	 SYNTAX Integer32
	 MAX-ACCESS read-only
	 STATUS current
	 DESCRIPTION
		 "cloud-cache-lookup"
	::= { statisticsStatsEntry 3 }

statisticsStatsCloudLookup OBJECT-TYPE
	 SYNTAX Integer32
	 MAX-ACCESS read-only
	 STATUS current
	 DESCRIPTION
		 "cloud-lookup"
	::= { statisticsStatsEntry 4 }

statisticsStatsRtuLookup OBJECT-TYPE
	 SYNTAX Integer32
	 MAX-ACCESS read-only
	 STATUS current
	 DESCRIPTION
		 "rtu-lookup"
	::= { statisticsStatsEntry 5 }

statisticsStatsLookupLatency OBJECT-TYPE
	 SYNTAX Integer32
	 MAX-ACCESS read-only
	 STATUS current
	 DESCRIPTION
		 "lookup-latency"
	::= { statisticsStatsEntry 6 }

statisticsStatsDbMem OBJECT-TYPE
	 SYNTAX Integer32
	 MAX-ACCESS read-only
	 STATUS current
	 DESCRIPTION
		 "db-mem"
	::= { statisticsStatsEntry 7 }

statisticsStatsRtuCacheMem OBJECT-TYPE
	 SYNTAX Integer32
	 MAX-ACCESS read-only
	 STATUS current
	 DESCRIPTION
		 "rtu-cache-mem"
	::= { statisticsStatsEntry 8 }

statisticsStatsLookupCacheMem OBJECT-TYPE
	 SYNTAX Integer32
	 MAX-ACCESS read-only
	 STATUS current
	 DESCRIPTION
		 "lookup-cache-mem"
	::= { statisticsStatsEntry 9 }

statisticsOperTable OBJECT-TYPE
	 SYNTAX SEQUENCE OF StatisticsOperEntry
	 MAX-ACCESS not-accessible
	 STATUS current
	 DESCRIPTION
		 "Statistics from object 'web-category.statistics'"
	::= {statistics 2}

statisticsOperEntry OBJECT-TYPE
	SYNTAX StatisticsOperEntry
	MAX-ACCESS not-accessible
	STATUS current
	DESCRIPTION
		"The statisticsOper entry"
	INDEX {
		statisticsOperSlotId
	}
	::= { statisticsOperTable 1 }

StatisticsOperEntry ::=
	SEQUENCE {
		statisticsOperSlotId Integer32,
		statisticsOperNumDplaneThreads	 Integer32,
		statisticsOperNumLookupThreads	 Integer32,
		statisticsOperTotalReqQueue	 Integer32,
		statisticsOperTotalReqDropped	 Integer32,
		statisticsOperTotalReqProcessed	 Integer32,
		statisticsOperTotalReqLookupProcessed	 Integer32,
		statisticsOperClearCache	 DisplayString
	}

statisticsOperSlotId OBJECT-TYPE
	 SYNTAX Integer32
	 MAX-ACCESS read-only
	 STATUS current
	 DESCRIPTION
		 ""
	::= { statisticsOperEntry 1 }

statisticsOperNumDplaneThreads OBJECT-TYPE
	 SYNTAX Integer32
	 MAX-ACCESS read-only
	 STATUS current
	 DESCRIPTION
		 "num-dplane-threads"
	::= { statisticsOperEntry 2 }

statisticsOperNumLookupThreads OBJECT-TYPE
	 SYNTAX Integer32
	 MAX-ACCESS read-only
	 STATUS current
	 DESCRIPTION
		 "num-lookup-threads"
	::= { statisticsOperEntry 3 }

statisticsOperTotalReqQueue OBJECT-TYPE
	 SYNTAX Integer32
	 MAX-ACCESS read-only
	 STATUS current
	 DESCRIPTION
		 "total-req-queue"
	::= { statisticsOperEntry 4 }

statisticsOperTotalReqDropped OBJECT-TYPE
	 SYNTAX Integer32
	 MAX-ACCESS read-only
	 STATUS current
	 DESCRIPTION
		 "total-req-dropped"
	::= { statisticsOperEntry 5 }

statisticsOperTotalReqProcessed OBJECT-TYPE
	 SYNTAX Integer32
	 MAX-ACCESS read-only
	 STATUS current
	 DESCRIPTION
		 "total-req-processed"
	::= { statisticsOperEntry 6 }

statisticsOperTotalReqLookupProcessed OBJECT-TYPE
	 SYNTAX Integer32
	 MAX-ACCESS read-only
	 STATUS current
	 DESCRIPTION
		 "total-req-lookup-processed"
	::= { statisticsOperEntry 7 }

statisticsOperClearCache OBJECT-TYPE
	 SYNTAX DisplayString
	 MAX-ACCESS read-only
	 STATUS current
	 DESCRIPTION
		 "clear-cache"
	::= { statisticsOperEntry 8 }

statisticsOperPerCpuListTable OBJECT-TYPE
	 SYNTAX SEQUENCE OF StatisticsOperPerCpuListEntry
	 MAX-ACCESS not-accessible
	 STATUS current
	 DESCRIPTION
		 "Statistics from object 'web-category.statistics'"
	::= {statistics 3}

statisticsOperPerCpuListEntry OBJECT-TYPE
	SYNTAX StatisticsOperPerCpuListEntry
	MAX-ACCESS not-accessible
	STATUS current
	DESCRIPTION
		"The statisticsOperPerCpuList entry:per-cpu-list"
	INDEX {
		statisticsOperPerCpuListSlotId,
		statisticsOperPerCpuListPerCpuListListId
	}
	::= { statisticsOperPerCpuListTable 1}

StatisticsOperPerCpuListEntry ::=
	SEQUENCE {
		statisticsOperPerCpuListSlotId Integer32,
		statisticsOperPerCpuListPerCpuListListId Integer32,
		statisticsOperPerCpuListReqQueue	Integer32,
		statisticsOperPerCpuListReqDropped	Integer32,
		statisticsOperPerCpuListReqProcessed	Integer32,
		statisticsOperPerCpuListReqLookupProcessed	Integer32
	}

statisticsOperPerCpuListSlotId OBJECT-TYPE
	SYNTAX Integer32
	MAX-ACCESS read-only
	STATUS current
	DESCRIPTION
		""
	::= { statisticsOperPerCpuListEntry 1}

statisticsOperPerCpuListPerCpuListListId OBJECT-TYPE
	SYNTAX Integer32
	MAX-ACCESS read-only
	STATUS current
	DESCRIPTION
		""
	::= { statisticsOperPerCpuListEntry 2}

statisticsOperPerCpuListReqQueue OBJECT-TYPE
	SYNTAX Integer32
	MAX-ACCESS read-only
	STATUS current
	DESCRIPTION
		"req-queue"
	::= { statisticsOperPerCpuListEntry 3}

statisticsOperPerCpuListReqDropped OBJECT-TYPE
	SYNTAX Integer32
	MAX-ACCESS read-only
	STATUS current
	DESCRIPTION
		"req-dropped"
	::= { statisticsOperPerCpuListEntry 4}

statisticsOperPerCpuListReqProcessed OBJECT-TYPE
	SYNTAX Integer32
	MAX-ACCESS read-only
	STATUS current
	DESCRIPTION
		"req-processed"
	::= { statisticsOperPerCpuListEntry 5}

statisticsOperPerCpuListReqLookupProcessed OBJECT-TYPE
	SYNTAX Integer32
	MAX-ACCESS read-only
	STATUS current
	DESCRIPTION
		"req-lookup-processed"
	::= { statisticsOperPerCpuListEntry 6}

END
