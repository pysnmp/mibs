-- =================================================================
-- Copyright (C) 2007 by H3C TECHNOLOGIES. All rights reserved.
--
-- Description: CATV transceiver MIB
-- Reference:
-- Version: V1.0
-- History:
-- V1.0 created by xujun.
--     Initial version of the MIB
-- =================================================================
H3C-CATV-TRANSCEIVER-MIB DEFINITIONS ::= BEGIN

IMPORTS
        h3cCommon
    FROM HUAWEI-3COM-OID-MIB
        Integer32, OBJECT-TYPE, MODULE-IDENTITY,
        NOTIFICATION-TYPE
    FROM SNMPv2-SMI;

h3cCATVTransceiver MODULE-IDENTITY
    LAST-UPDATED "200807251008Z"
    ORGANIZATION
        "Hangzhou H3C Tech. Co., Ltd."
    CONTACT-INFO
        "SMB BG Team H3C Technologies Co., Ltd.
        310 Liuhe Road, Zhijiang Science Park, Hangzhou, P.R.China
        http://www.h3c.com
        Zip:310053."
    DESCRIPTION
        "
        The objects in this MIB module are used to manage and
        display common configuration for CATV(Community Antenna
        Television) transceiver module.
        "
    ::= { h3cCommon 94 }

--
-- h3cCATVTransceiverStatus
--

h3cCATVTransStatus OBJECT IDENTIFIER ::= { h3cCATVTransceiver 1 }

h3cCATVTransStatusScalarObjects OBJECT IDENTIFIER ::= { h3cCATVTransStatus 1 }

h3cCATVTransState OBJECT-TYPE
    SYNTAX     INTEGER
    {
        on         (1),
        off        (2)
    }
    MAX-ACCESS read-only
    STATUS     current
    DESCRIPTION
         "
         The state of CATV transceiver.
         "
    ::= { h3cCATVTransStatusScalarObjects 1 }

h3cCATVTransInputPwr OBJECT-TYPE
    SYNTAX     Integer32
    UNITS      "dbm"
    MAX-ACCESS read-only
    STATUS     current
    DESCRIPTION
         "
         The input power of CATV transceiver.
         If transceiver is not on site,
         the value should be zero.
         "
    ::= { h3cCATVTransStatusScalarObjects 2 }

h3cCATVTransOutputLevel OBJECT-TYPE
    SYNTAX     Integer32
    UNITS      "dbuv"
    MAX-ACCESS read-only
    STATUS     current
    DESCRIPTION
         "
         The output level of CATV transceiver.
         If transceiver is not on site,
         the value should be zero.
         "
    ::= { h3cCATVTransStatusScalarObjects 3 }

h3cCATVTransTemperature OBJECT-TYPE
    SYNTAX     Integer32
    UNITS      "centigrade"
    MAX-ACCESS read-only
    STATUS     current
    DESCRIPTION
         "
         The temperature of CATV transceiver.
         If transceiver is not on site,
         the value should be zero.
         "
    ::= { h3cCATVTransStatusScalarObjects 4 }


--
-- h3cCATVTransceiverMan
--

h3cCATVTransceiverMan OBJECT IDENTIFIER ::= { h3cCATVTransceiver 2 }

h3cCATVTransCtrlScalarObjects OBJECT IDENTIFIER ::= { h3cCATVTransceiverMan 1 }

h3cCATVTransInputPwrLowerThr OBJECT-TYPE
    SYNTAX     Integer32
    UNITS      "dbm"
    MAX-ACCESS read-write
    STATUS     current
    DESCRIPTION
        "
        A threshold for the CATV transceiver's input power.
        When the input power of CATV transceiver is lower
        than threshold, a trap should be generated.
        "
    ::= { h3cCATVTransCtrlScalarObjects 1 }

h3cCATVTransOutputLvlLowerThr OBJECT-TYPE
    SYNTAX     Integer32
    UNITS      "dbuv"
    MAX-ACCESS read-write
    STATUS     current
    DESCRIPTION
        "
        A threshold for the CATV transceiver's output level.
        When the output level of CATV transceiver is lower
        than threshold, a trap should be generated.
        "
    ::= { h3cCATVTransCtrlScalarObjects 2 }

h3cCATVTransTempratureUpperThr OBJECT-TYPE
    SYNTAX     Integer32
    UNITS      "¡æ"
    MAX-ACCESS read-write
    STATUS     current
    DESCRIPTION
        "
        A threshold for the CATV transceiver's temperature.
        When the temperature of CATV transceiver is higher
        than threshold, a trap should be generated.
        "
    ::= { h3cCATVTransCtrlScalarObjects 3 }


--
-- h3cCATVTransceiver NOTIFICATION
--

h3cCATVTansTrap OBJECT IDENTIFIER ::= { h3cCATVTransceiver 3 }

h3cCATVTransTrapPrefix OBJECT IDENTIFIER ::= {h3cCATVTansTrap 0}

h3cCATVTransInputPwrTrap NOTIFICATION-TYPE
    OBJECTS
        {
            h3cCATVTransInputPwr
        }
    STATUS current
    DESCRIPTION
        "
        A h3cCATVTransInputPwrTrap notification is sent when the
        input power of CATV transceiver is lower than the threshold.
        "
    ::= { h3cCATVTransTrapPrefix 1 }

h3cCATVTransInputPwrReTrap NOTIFICATION-TYPE
    OBJECTS
        {
            h3cCATVTransInputPwr
        }
    STATUS current
    DESCRIPTION
        "
        A h3cCATVTransInputPwrReTrap notification is sent when the
        input power of CATV transceiver recovered from the last trap.
        "
    ::= { h3cCATVTransTrapPrefix 2 }

h3cCATVTransOutputLvlTrap NOTIFICATION-TYPE
    OBJECTS
        {
            h3cCATVTransOutputLevel
        }
    STATUS current
    DESCRIPTION
        "
        A h3cCATVTransOutputLvlTrap notification is sent when the
        output level of CATV transceiver is lower than the threshold.
        "
    ::= { h3cCATVTransTrapPrefix 3 }

h3cCATVTransOutputLvlReTrap NOTIFICATION-TYPE
    OBJECTS
        {
            h3cCATVTransOutputLevel
        }
    STATUS current
    DESCRIPTION
        "
        A h3cCATVTransOutputLvlReTrap notification is sent when the
        output level of CATV transceiver recovered from the last trap.
        "
    ::= { h3cCATVTransTrapPrefix 4 }

h3cCATVTransTemperatureTrap NOTIFICATION-TYPE
    OBJECTS
        {
            h3cCATVTransTemperature
        }
    STATUS current
    DESCRIPTION
        "
        A h3cCATVTransTemperatureTrap notification is sent when the
        temperature of CATV transceiver is higher than the threshold.
        "
    ::= { h3cCATVTransTrapPrefix 5 }

h3cCATVTransTemperatureReTrap NOTIFICATION-TYPE
    OBJECTS
        {
            h3cCATVTransTemperature
        }
    STATUS current
    DESCRIPTION
        "
        A h3cCATVTransTemperatureReTrap notification is sent when the
        temperature of CATV transceiver recovered from the last trap.
        "
    ::= { h3cCATVTransTrapPrefix 6 }
END
