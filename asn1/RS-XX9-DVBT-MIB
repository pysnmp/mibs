--
-- RS-XX9-DVBT-MIB.mi2
-- MIB generated by MG-SOFT Visual MIB Builder 2010 Version 8.0  Build 403
-- Monday, March 09, 2015 at 14:23:35
--

-- *****************************************************************************
-- *****************************************************************************
-- **
-- **  COPYRIGHT      (c) 2012 Rohde & Schwarz GmbH & Co. KG
-- **                          Muehldorfstrasse 15
-- **    R & S                 D-81671 Muenchen
-- **
-- *****************************************************************************
-- **
-- **  MODULE         RS-XX9-DVBT-MIB
-- **  
-- *****************************************************************************
-- *****************************************************************************

    RS-XX9-DVBT-MIB DEFINITIONS ::= BEGIN
 
        IMPORTS
            commonNotificationAlarmClass            
                FROM RS-XX9-COMMON-MIB            
            rsXx9DvbT, rsXx9MibModule            
                FROM RS-XX9-SMI-MIB            
            NotificationMask, NotificationPriority, NotificationState, IndexTransmitter, IndexAB, 
            SwitchOnOff            
                FROM RS-XX9-TC-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI            
            TruthValue, TEXTUAL-CONVENTION            
                FROM SNMPv2-TC;
    
    
        rsXx9DvbtMibModule MODULE-IDENTITY 
            LAST-UPDATED "201412221600Z"		-- December 22, 2014 at 16:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines DVB-T specific objects
                of XX9000 transmitting systems from Rohde & Schwarz.
                
                The following MIBs are related to this:
                - RS-COMMON-MIB         - mandatory for this MIB
                - RS-XX9-SMI-MIB        - mandatory for this MIB
                - RS-XX9-TC-MIB         - mandatory for this MIB
                - RS-XX9-COMMON-MIB     - mandatory for this MIB"
            REVISION "201412221600Z"		-- December 22, 2014 at 16:00 GMT
            DESCRIPTION 
                "updated description texts
                "
            REVISION "201402051600Z"		-- February 05, 2014 at 16:00 GMT
            DESCRIPTION 
                "initial release.
                update description texts"
            REVISION "201202230800Z"		-- February 23, 2012 at 08:00 GMT
            DESCRIPTION 
                "Preliminary version."
            ::= { rsXx9MibModule 6 }

        
    
--
-- Textual conventions
--
    
        DvbtChannelBandwidth ::= TEXTUAL-CONVENTION
            STATUS current
            DESCRIPTION 
                "mhz5(4)   -  5 MHz
                mhz6(5)   -  6 MHz
                mhz7(6)   -  7 MHz
                mhz8(7)   -  8 MHz"
            SYNTAX INTEGER
                {
                undefined(1),
                mhz5(4),
                mhz6(5),
                mhz7(6),
                mhz8(7)
                }

        DvbtFftSize ::= TEXTUAL-CONVENTION
            STATUS current
            DESCRIPTION 
                "FFT size:
                k2(3) - the OFDM signal is modulated on 1705 sub-carriers
                k8(4) - 6817 subcarriers are used
                
                k4(4) - only for DVB-H"
            SYNTAX INTEGER
                {
                undefined(1),
                k2(3),
                k4(4),
                k8(5)
                }

        DvbtGuardInterval ::= TEXTUAL-CONVENTION
            STATUS current
            DESCRIPTION 
                "Guard interval.
                oneDiv32(2)       -> 1/32
                oneDiv16(3)       -> 1/16
                oneDiv8(4)        -> 1/8
                oneDiv4(5)        -> 1/4"
            SYNTAX INTEGER
                {
                undefined(1),
                oneDiv32(2),
                oneDiv16(3),
                oneDiv8(4),
                oneDiv4(5)
                }

        DvbtModulation ::= TEXTUAL-CONVENTION
            STATUS current
            DESCRIPTION 
                "qpsk(4)  - is very fail safe but only allows low data rate.
                qam64(6) - 64 QAM can transport a huge amount of data in good
                           radio reception environments"
            SYNTAX INTEGER
                {
                undefined(1),
                qpsk(4),
                qam16(5),
                qam64(6)
                }

        DvbtCodeRate ::= TEXTUAL-CONVENTION
            STATUS current
            DESCRIPTION 
                "The code rate sets the ratio between payload and
                error correction information."
            SYNTAX INTEGER
                {
                undefined(1),
                oneHalf(2),
                twoThird(4),
                threeFourth(5),
                fiveSixth(7),
                sevenEighth(8)
                }

        DvbtInterleave ::= TEXTUAL-CONVENTION
            STATUS current
            DESCRIPTION 
                "Process according to which the bit interleaver interleaves its data.
                Meaningful only for DVBT-H."
            SYNTAX INTEGER
                {
                nat(1),
                inDepth(2)
                }

    
--
-- Node definitions
--
    
        rsXx9DvbtNotifications OBJECT IDENTIFIER ::= { rsXx9DvbT 0 }

        
        dvbtEncoderSummary NOTIFICATION-TYPE
            OBJECTS { commonNotificationAlarmClass, dvbtStatusNotificationPriority, dvbtStatusNotificationState }
            STATUS current
            DESCRIPTION 
                "Encoder summary state.
                
                Possible values:
                off(2)
                fault(3)
                warning(4)
                ok(5)
                
                Notification class: fault"
            ::= { rsXx9DvbtNotifications 1 }

        
        dvbtTest NOTIFICATION-TYPE
            OBJECTS { commonNotificationAlarmClass, dvbtStatusNotificationPriority, dvbtStatusNotificationState }
            STATUS current
            DESCRIPTION 
                "One of the test signals is activated. 
                If a test signal is activated, decoding 
                of the transmitted signal by the 
                transmitter will not be possible.
                
                Possible values:
                off(2)     - no test signal generation
                warning(4) - test signal generation is activated
                
                Notification class: warning"
            ::= { rsXx9DvbtNotifications 2 }

        
        rsXx9DvbtObjects OBJECT IDENTIFIER ::= { rsXx9DvbT 1 }

        
        dvbtStatus OBJECT IDENTIFIER ::= { rsXx9DvbtObjects 1 }

        
        dvbtStatusNotificationTable OBJECT-TYPE
            SYNTAX SEQUENCE OF DvbtStatusNotificationEntry
            MAX-ACCESS not-accessible
            STATUS current
            DESCRIPTION
                "The context information/configuration for the
                DVB-T status notifications."
            ::= { dvbtStatus 1 }

        
        dvbtStatusNotificationEntry OBJECT-TYPE
            SYNTAX DvbtStatusNotificationEntry
            MAX-ACCESS not-accessible
            STATUS current
            DESCRIPTION
                "An entry in the dvbtStatusNotificationTable."
            INDEX { dvbtStatusNotificationTxIdx, dvbtStatusNotificationExcIdx, dvbtStatusNotificationIdx }
            ::= { dvbtStatusNotificationTable 1 }

        
        DvbtStatusNotificationEntry ::=
            SEQUENCE { 
                dvbtStatusNotificationTxIdx
                    IndexTransmitter,
                dvbtStatusNotificationExcIdx
                    IndexAB,
                dvbtStatusNotificationIdx
                    Unsigned32,
                dvbtStatusNotificationName
                    INTEGER,
                dvbtStatusNotificationMask
                    NotificationMask,
                dvbtStatusNotificationPriority
                    NotificationPriority,
                dvbtStatusNotificationState
                    NotificationState
             }

        dvbtStatusNotificationTxIdx OBJECT-TYPE
            SYNTAX IndexTransmitter
            MAX-ACCESS not-accessible
            STATUS current
            DESCRIPTION
                "The transmitter index."
            ::= { dvbtStatusNotificationEntry 1 }

        
        dvbtStatusNotificationExcIdx OBJECT-TYPE
            SYNTAX IndexAB
            MAX-ACCESS not-accessible
            STATUS current
            DESCRIPTION
                "This index distinguishes the exiters.
                Necessary if you have dual drive transmitters."
            ::= { dvbtStatusNotificationEntry 2 }

        
        dvbtStatusNotificationIdx OBJECT-TYPE
            SYNTAX Unsigned32 (1..2)
            MAX-ACCESS not-accessible
            STATUS current
            DESCRIPTION
                "The notification number as below rsXx9DvbtNotifications.
                This is a helper column and therefore not-accessible."
            ::= { dvbtStatusNotificationEntry 3 }

        
        dvbtStatusNotificationName OBJECT-TYPE
            SYNTAX INTEGER
                {
                dvbtEncoderSummary(1),
                dvbtTest(2)
                }
            MAX-ACCESS read-write
            STATUS current
            DESCRIPTION
                "The notification number as an enumeration.
                The enumeration correlates with the notifications under rsXx9DvbtNotifications."
            ::= { dvbtStatusNotificationEntry 4 }

        
        dvbtStatusNotificationMask OBJECT-TYPE
            SYNTAX NotificationMask
            MAX-ACCESS read-write
            STATUS current
            DESCRIPTION
                "See textual convention for details."
            ::= { dvbtStatusNotificationEntry 5 }

        
        dvbtStatusNotificationPriority OBJECT-TYPE
            SYNTAX NotificationPriority
            MAX-ACCESS read-write
            STATUS current
            DESCRIPTION
                "See textual convention for details."
            ::= { dvbtStatusNotificationEntry 6 }

        
        dvbtStatusNotificationState OBJECT-TYPE
            SYNTAX NotificationState
            MAX-ACCESS read-only
            STATUS current
            DESCRIPTION
                "See textual convention for details."
            ::= { dvbtStatusNotificationEntry 7 }

        
        dvbtStateTable OBJECT-TYPE
            SYNTAX SEQUENCE OF DvbtStateEntry
            MAX-ACCESS not-accessible
            STATUS current
            DESCRIPTION
                "DVB-T state values."
            ::= { dvbtStatus 2 }

        
        dvbtStateEntry OBJECT-TYPE
            SYNTAX DvbtStateEntry
            MAX-ACCESS not-accessible
            STATUS current
            DESCRIPTION
                "An entry in the dvbtStateTable."
            INDEX { dvbtStatusNotificationTxIdx, dvbtStatusNotificationExcIdx }
            ::= { dvbtStateTable 1 }

        
        DvbtStateEntry ::=
            SEQUENCE { 
                dvbtStTxFrequencyOffset
                    Integer32,
                dvbtStTxDelayOffset
                    Integer32,
                dvbtStCellId
                    INTEGER
             }

        dvbtStTxFrequencyOffset OBJECT-TYPE
            SYNTAX Integer32
            UNITS "Hz"
            MAX-ACCESS read-only
            STATUS current
            DESCRIPTION
                "Number of Hertz by which this transmitter is to 
                shift its transmission frequency relative to other 
                transmitters of the DVB-T network.
                This value is configured via the MIP (megaframe initialization packet)."
            ::= { dvbtStateEntry 1 }

        
        dvbtStTxDelayOffset OBJECT-TYPE
            SYNTAX Integer32
            UNITS "1/10 micro second"
            MAX-ACCESS read-only
            STATUS current
            DESCRIPTION
                "Time by which this transmitter is to shift 
                the time of transmission of its signal relative 
                to other transmitters of the DVB-T network.
                This value is configured via the MIP (megaframe initialization packet)."
            ::= { dvbtStateEntry 2 }

        
        dvbtStCellId OBJECT-TYPE
            SYNTAX INTEGER
                {
                disabled(1),
                ok(2),
                notPresent(3),
                txControlDisabled(4),
                txAddressFail(5),
                mipFail(6)
                }
            MAX-ACCESS read-only
            STATUS current
            DESCRIPTION
                "shows if a Cell ID has been found in the 
                transport stream, which matches the 
                configured transmitter ID."
            ::= { dvbtStateEntry 3 }

        
        dvbtSetup OBJECT IDENTIFIER ::= { rsXx9DvbtObjects 2 }

        
        dvbtConfigurationTable OBJECT-TYPE
            SYNTAX SEQUENCE OF DvbtConfigurationEntry
            MAX-ACCESS not-accessible
            STATUS current
            DESCRIPTION
                "General DVB-T configuration."
            ::= { dvbtSetup 1 }

        
        dvbtConfigurationEntry OBJECT-TYPE
            SYNTAX DvbtConfigurationEntry
            MAX-ACCESS not-accessible
            STATUS current
            DESCRIPTION
                "An entry in the dvbtConfigurationTable."
            INDEX { dvbtConfigurationTxIdx, dvbtConfigurationExcIdx }
            ::= { dvbtConfigurationTable 1 }

        
        DvbtConfigurationEntry ::=
            SEQUENCE { 
                dvbtConfigurationTxIdx
                    IndexTransmitter,
                dvbtConfigurationExcIdx
                    IndexAB,
                dvbtConfigurationModulationSource
                    INTEGER,
                dvbtConfigurationDigitalMode
                    INTEGER
             }

        dvbtConfigurationTxIdx OBJECT-TYPE
            SYNTAX IndexTransmitter
            MAX-ACCESS not-accessible
            STATUS current
            DESCRIPTION
                "The transmitter index."
            ::= { dvbtConfigurationEntry 1 }

        
        dvbtConfigurationExcIdx OBJECT-TYPE
            SYNTAX IndexAB
            MAX-ACCESS not-accessible
            STATUS current
            DESCRIPTION
                "This index distinguishes the exiters.
                Necessary if you have dual drive transmitters."
            ::= { dvbtConfigurationEntry 2 }

        
        dvbtConfigurationModulationSource OBJECT-TYPE
            SYNTAX INTEGER
                {
                undefined(1),
                mip(2),
                manual(3)
                }
            MAX-ACCESS read-write
            STATUS current
            DESCRIPTION
                "The source for the TPS (transmission parameter signaling) 
                parameters is configured here. 
                Possible sources are the MIP (megaframe initialization packet) 
                or manually selected default settings.
                "
            ::= { dvbtConfigurationEntry 3 }

        
        dvbtConfigurationDigitalMode OBJECT-TYPE
            SYNTAX INTEGER
                {
                undefined(1),
                dvbT(2),
                dvbH(3)
                }
            MAX-ACCESS read-write
            STATUS current
            DESCRIPTION
                "Selection of digital TV standard."
            ::= { dvbtConfigurationEntry 4 }

        
        dvbtLocalizationTable OBJECT-TYPE
            SYNTAX SEQUENCE OF DvbtLocalizationEntry
            MAX-ACCESS not-accessible
            STATUS current
            DESCRIPTION
                "DVB-T localization parameters."
            ::= { dvbtSetup 2 }

        
        dvbtLocalizationEntry OBJECT-TYPE
            SYNTAX DvbtLocalizationEntry
            MAX-ACCESS not-accessible
            STATUS current
            DESCRIPTION
                "An entry in the dvbtLocalizationTable."
            AUGMENTS { dvbtConfigurationEntry }
            ::= { dvbtLocalizationTable 1 }

        
        DvbtLocalizationEntry ::=
            SEQUENCE { 
                dvbtLocalizationTxControl
                    INTEGER,
                dvbtLocalizationTxAddress
                    Unsigned32,
                dvbtLocalizationCellIdSource
                    INTEGER,
                dvbtLocalizationCellId
                    Unsigned32
             }

        dvbtLocalizationTxControl OBJECT-TYPE
            SYNTAX INTEGER
                {
                undefined(1),
                on(2),
                off(3)
                }
            MAX-ACCESS read-write
            STATUS current
            DESCRIPTION
                "If set to on(2) and if dvbtLocalizationTxAddress is valid,
                the Cell ID, the frequency offset, and the delay offset from the 
                MIP (megaframe initialization packet) are applied.
                "
            ::= { dvbtLocalizationEntry 1 }

        
        dvbtLocalizationTxAddress OBJECT-TYPE
            SYNTAX Unsigned32 (0..65535)
            MAX-ACCESS read-write
            STATUS current
            DESCRIPTION
                "Transmitter address.
                Setting the transmitter address is a precondition to reading 
                Tx information (transmitter-specific settings) from the MIP 
                (Megaframe Initialization Packet). However, the information 
                is used only if dvbtLocalizationTxControl is enabled."
            ::= { dvbtLocalizationEntry 2 }

        
        dvbtLocalizationCellIdSource OBJECT-TYPE
            SYNTAX INTEGER
                {
                undefined(1),
                mip(2),
                manual(3)
                }
            MAX-ACCESS read-write
            STATUS current
            DESCRIPTION
                "Selects the data source of the Cell ID. The signaling of the Cell ID can be switched off here."
            ::= { dvbtLocalizationEntry 3 }

        
        dvbtLocalizationCellId OBJECT-TYPE
            SYNTAX Unsigned32 (0..65535)
            MAX-ACCESS read-write
            STATUS current
            DESCRIPTION
                "Defines what Cell ID this transmitter should use according 
                to Individual Addressing information. 
                This value can be applied from the MIP (when dvbtLocalizationCellIdSource is set to mip(2)).
                However, the Cell ID can also be configured here 
                manually if necessary (dvbtLocalizationCellIdSource set to manual(3)).
                "
            ::= { dvbtLocalizationEntry 4 }

        
        dvbtModulationTable OBJECT-TYPE
            SYNTAX SEQUENCE OF DvbtModulationEntry
            MAX-ACCESS not-accessible
            STATUS current
            DESCRIPTION
                "DVB-T modulation parameters."
            ::= { dvbtSetup 3 }

        
        dvbtModulationEntry OBJECT-TYPE
            SYNTAX DvbtModulationEntry
            MAX-ACCESS not-accessible
            STATUS current
            DESCRIPTION
                "An entry in the dvbtModulationTable."
            AUGMENTS { dvbtConfigurationEntry }
            ::= { dvbtModulationTable 1 }

        
        DvbtModulationEntry ::=
            SEQUENCE { 
                dvbtModulationChannelBandwidth
                    DvbtChannelBandwidth,
                dvbtModulationFftMode
                    DvbtFftSize,
                dvbtModulationGuardInterval
                    DvbtGuardInterval,
                dvbtModulationConstellation
                    DvbtModulation,
                dvbtModulationCodeRate
                    DvbtCodeRate,
                dvbtModulationMpeFEC
                    SwitchOnOff,
                dvbtModulationTimeSlicing
                    SwitchOnOff,
                dvbtModulationInterleave
                    DvbtInterleave
             }

        dvbtModulationChannelBandwidth OBJECT-TYPE
            SYNTAX DvbtChannelBandwidth
            MAX-ACCESS read-write
            STATUS current
            DESCRIPTION
                "Channel bandwidth occupied by the DVB-T signal in the 
                frequency spectrum. You can configure 5, 6, 7, or 8 MHz. 
                The choice depends on the required bandwidth of the 
                channel to be transmitted. 
                "
            ::= { dvbtModulationEntry 3 }

        
        dvbtModulationFftMode OBJECT-TYPE
            SYNTAX DvbtFftSize
            MAX-ACCESS read-write
            STATUS current
            DESCRIPTION
                "The FFT length corresponds to the number of carriers used. 
                The setting depends on the customized decision concerning 
                your DVB network.The OFDM signal is modeled at 2K on 1705 carriers 
                and at 8K on 6817 carriers. 
                The setting of 4K can be selected only for DVB-H.
                "
            ::= { dvbtModulationEntry 4 }

        
        dvbtModulationGuardInterval OBJECT-TYPE
            SYNTAX DvbtGuardInterval
            MAX-ACCESS read-write
            STATUS current
            DESCRIPTION
                "The Guard Interval determines the time span between 
                signals for multicarrier modulation, in which no information 
                is transmitted. The larger the time span is, the lower the 
                risk of interference and the lower the data transfer rate. 
                The setting values are a fraction of the symbol period. 
                Ideally, you select a value that is larger than the longest 
                echo travel time of the system. 
                Possible setting values are: 
                1/32, 1/16, 1/8, 1/4, 
                whereby the risk of interference is greatest at 1/32, 
                but the data transfer rate, in turn, is highest.
                "
            ::= { dvbtModulationEntry 5 }

        
        dvbtModulationConstellation OBJECT-TYPE
            SYNTAX DvbtModulation
            MAX-ACCESS read-write
            STATUS current
            DESCRIPTION
                "Sets up the modulation mode.
                QPSK is very fail-safe, but has only a small data rate. 
                64 QAM can transmit very large data rates if you expect few faults on the transmission link. 
                16 QAM is a compromise between the two other setting values."
            ::= { dvbtModulationEntry 6 }

        
        dvbtModulationCodeRate OBJECT-TYPE
            SYNTAX DvbtCodeRate
            MAX-ACCESS read-write
            STATUS current
            DESCRIPTION
                "With the code rate you can configure the relationship 
                between user data and (error correction values+user data). 
                Possible values are 1/2, 2/3, 3/4, 5/6, 7/8. 
                The greatest error correction and the lowest data transfer rate are enabled by 1/2, 
                and the lowest error correction and greatest data transfer rate are enabled by 7/8.
                "
            ::= { dvbtModulationEntry 7 }

        
        dvbtModulationMpeFEC OBJECT-TYPE
            SYNTAX SwitchOnOff
            MAX-ACCESS read-write
            STATUS current
            DESCRIPTION
                "Switches the forward error correction on or off.
                This parameter is operative for DVB-H only.
                "
            ::= { dvbtModulationEntry 8 }

        
        dvbtModulationTimeSlicing OBJECT-TYPE
            SYNTAX SwitchOnOff
            MAX-ACCESS read-write
            STATUS current
            DESCRIPTION
                "The transmission of the payload in time slices is activated by this.
                It enables energy-efficient operation of the receivers,
                since these can disable their input stages during pauses in transmission.
                This parameter is operative for DVB-H only.
                "
            ::= { dvbtModulationEntry 9 }

        
        dvbtModulationInterleave OBJECT-TYPE
            SYNTAX DvbtInterleave
            MAX-ACCESS read-write
            STATUS current
            DESCRIPTION
                "Process according to which the bit interleaver interleaves its data. 
                This parameter is operative only for DVB-H.
                "
            ::= { dvbtModulationEntry 10 }

        
        dvbtTestTable OBJECT-TYPE
            SYNTAX SEQUENCE OF DvbtTestEntry
            MAX-ACCESS not-accessible
            STATUS current
            DESCRIPTION
                "Configures the test mode of the exciter."
            ::= { dvbtSetup 4 }

        
        dvbtTestEntry OBJECT-TYPE
            SYNTAX DvbtTestEntry
            MAX-ACCESS not-accessible
            STATUS current
            DESCRIPTION
                "An entry in the dvbtTestTable."
            AUGMENTS { dvbtConfigurationEntry }
            ::= { dvbtTestTable 1 }

        
        DvbtTestEntry ::=
            SEQUENCE { 
                dvbtTestMode
                    INTEGER
             }

        dvbtTestMode OBJECT-TYPE
            SYNTAX INTEGER
                {
                off(1),
                prbs(2),
                singleCarrier(3),
                mute1P1SymOfSuperFrame(6)
                }
            MAX-ACCESS read-write
            STATUS current
            DESCRIPTION
                "Which test signal is to be generated.
                
                off(1)  -  switches off test signal generation.
                prbs(2)  -  Generates a pseudo-random binary sequence insted of the payload. 
                singleCarrier(3) - Generates an unmodulated single carrier. 
                    This test signal can be used to measure the phase noise of the synthesizer. 
                mute1SymOfMegaFrame(6)  -  Suppresses the first symbol of each T2 frame. 
                    This function can be used to measure the time of signal transmission. 
                
                The phase noise must be measured via the RF Monitor Out connector (X61). 
                The cable connected to RF Out (X60) must be removed. 
                In order to protect the amplifiers, this test signal is only generated if the output of the exciter is open.
                "
            ::= { dvbtTestEntry 1 }

        
        dvbtOutput OBJECT IDENTIFIER ::= { rsXx9DvbtObjects 3 }

        
        dvbtOutLocalizationTable OBJECT-TYPE
            SYNTAX SEQUENCE OF DvbtOutLocalizationEntry
            MAX-ACCESS not-accessible
            STATUS current
            DESCRIPTION
                "Currently active DVB-T localization parameters."
            ::= { dvbtOutput 2 }

        
        dvbtOutLocalizationEntry OBJECT-TYPE
            SYNTAX DvbtOutLocalizationEntry
            MAX-ACCESS not-accessible
            STATUS current
            DESCRIPTION
                "An entry in the dvbtOutLocalizationTable."
            AUGMENTS { dvbtConfigurationEntry }
            ::= { dvbtOutLocalizationTable 1 }

        
        DvbtOutLocalizationEntry ::=
            SEQUENCE { 
                dvbtOutLocalizationCellId
                    Unsigned32
             }

        dvbtOutLocalizationCellId OBJECT-TYPE
            SYNTAX Unsigned32
            MAX-ACCESS read-write
            STATUS current
            DESCRIPTION
                "The currently used cell ID.
                "
            ::= { dvbtOutLocalizationEntry 4 }

        
        dvbtOutModulationTable OBJECT-TYPE
            SYNTAX SEQUENCE OF DvbtOutModulationEntry
            MAX-ACCESS not-accessible
            STATUS current
            DESCRIPTION
                "Currently active DVB-T modulation parameters."
            ::= { dvbtOutput 3 }

        
        dvbtOutModulationEntry OBJECT-TYPE
            SYNTAX DvbtOutModulationEntry
            MAX-ACCESS not-accessible
            STATUS current
            DESCRIPTION
                "An entry in the dvbtOutModulationTable."
            AUGMENTS { dvbtConfigurationEntry }
            ::= { dvbtOutModulationTable 1 }

        
        DvbtOutModulationEntry ::=
            SEQUENCE { 
                dvbtOutModulationChannelBandwidth
                    DvbtChannelBandwidth,
                dvbtOutModulationFftMode
                    DvbtFftSize,
                dvbtOutModulationGuardInterval
                    DvbtGuardInterval,
                dvbtOutModulationConstellation
                    DvbtModulation,
                dvbtOutModulationCodeRate
                    DvbtCodeRate,
                dvbtOutModulationMpeFEC
                    TruthValue,
                dvbtOutModulationTimeSlicing
                    TruthValue,
                dvbtOutModulationInterleave
                    DvbtInterleave
             }

        dvbtOutModulationChannelBandwidth OBJECT-TYPE
            SYNTAX DvbtChannelBandwidth
            MAX-ACCESS read-only
            STATUS current
            DESCRIPTION
                "Channel bandwidth occupied by the DVB-T signal in the 
                frequency spectrum. You can configure 5, 6, 7, or 8 MHz. 
                The choice depends on the required bandwidth of the 
                channel to be transmitted. 
                "
            ::= { dvbtOutModulationEntry 3 }

        
        dvbtOutModulationFftMode OBJECT-TYPE
            SYNTAX DvbtFftSize
            MAX-ACCESS read-only
            STATUS current
            DESCRIPTION
                "The amount of used subcarriers. 
                The FFT length corresponds to the number of carriers used. 
                The setting depends on the customized decision concerning 
                your DVB network.The OFDM signal is modeled at 2K on 1705 carriers 
                and at 8K on 6817 carriers. 
                The setting of 4K can be selected only for DVB-H.
                "
            ::= { dvbtOutModulationEntry 4 }

        
        dvbtOutModulationGuardInterval OBJECT-TYPE
            SYNTAX DvbtGuardInterval
            MAX-ACCESS read-only
            STATUS current
            DESCRIPTION
                "The time where no information is sent in relation to the
                bit on air time. This value affects the error correction
                in multipath receiving situations. A long Guard Interval
                reduces the amount of payload data.
                
                The time span between signals for multicarrier modulation, 
                in which no information is transmitted. The larger the time 
                span is, the lower the risk of interference and the lower the 
                data transfer rate. The setting values are a fraction of the 
                symbol period. Ideally, you select a value that is larger than 
                the longest echo travel time of the system. 
                Possible setting values are: 
                1/32, 1/16, 1/8, 1/4, 
                whereby the risk of interference is greatest at 1/32, 
                but the data transfer rate, in turn, is highest.
                "
            ::= { dvbtOutModulationEntry 5 }

        
        dvbtOutModulationConstellation OBJECT-TYPE
            SYNTAX DvbtModulation
            MAX-ACCESS read-only
            STATUS current
            DESCRIPTION
                "Shows the modulation mode.
                QPSK is very fail-safe, but has only a small data rate. 
                64 QAM can transmit very large data rates if you expect few faults on the transmission link. 
                16 QAM is a compromise between the two other setting values."
            ::= { dvbtOutModulationEntry 6 }

        
        dvbtOutModulationCodeRate OBJECT-TYPE
            SYNTAX DvbtCodeRate
            MAX-ACCESS read-only
            STATUS current
            DESCRIPTION
                "With the code rate you can configure the relationship 
                between user data and (error correction values+user data). 
                Possible values are 1/2, 2/3, 3/4, 5/6, 7/8. 
                The greatest error correction and the lowest data transfer rate are enabled by 1/2, 
                and the lowest error correction and greatest data transfer rate are enabled by 7/8.
                "
            ::= { dvbtOutModulationEntry 7 }

        
        dvbtOutModulationMpeFEC OBJECT-TYPE
            SYNTAX TruthValue
            MAX-ACCESS read-only
            STATUS current
            DESCRIPTION
                "Shows whether the forward error correction is on or off.
                This parameter is meaningful for DVB-H only.
                "
            ::= { dvbtOutModulationEntry 8 }

        
        dvbtOutModulationTimeSlicing OBJECT-TYPE
            SYNTAX TruthValue
            MAX-ACCESS read-only
            STATUS current
            DESCRIPTION
                "Shows the activation of the transmission of the payload in time slices.
                It enables energy-efficient operation of the receivers,
                since these can disable their input stages during pauses in transmission.
                This parameter is meaningful for DVB-H only.
                "
            ::= { dvbtOutModulationEntry 9 }

        
        dvbtOutModulationInterleave OBJECT-TYPE
            SYNTAX DvbtInterleave
            MAX-ACCESS read-only
            STATUS current
            DESCRIPTION
                "Process according to which the bit interleaver interleaves its data. 
                This parameter is meaningful for DVB-H only.
                "
            ::= { dvbtOutModulationEntry 10 }

        
        rsXx9DvbtConformance OBJECT IDENTIFIER ::= { rsXx9DvbT 2 }

        
        rsXx9DvbtCompliances OBJECT IDENTIFIER ::= { rsXx9DvbtConformance 1 }

        
        dvbtBasicCompliance MODULE-COMPLIANCE
            STATUS current
            DESCRIPTION 
                "The compliance statement for XX9000 DVB-T encoding."
            MODULE -- this module
                MANDATORY-GROUPS { dvbtObjBasic, dvbtNotifyBasic }
                GROUP dvbtObjDvbH
                    DESCRIPTION 
                        "For DVB-H only."
            ::= { rsXx9DvbtCompliances 1 }

        
        rsXx9DvbtGroups OBJECT IDENTIFIER ::= { rsXx9DvbtConformance 2 }

        
        dvbtObjBasic OBJECT-GROUP
            OBJECTS { dvbtStatusNotificationName, dvbtStatusNotificationMask, dvbtStatusNotificationPriority, dvbtStatusNotificationState, dvbtConfigurationModulationSource, 
                dvbtModulationChannelBandwidth, dvbtModulationFftMode, dvbtModulationGuardInterval, dvbtModulationConstellation, dvbtModulationCodeRate, 
                dvbtLocalizationCellId, dvbtLocalizationCellIdSource, dvbtLocalizationTxAddress, dvbtLocalizationTxControl, dvbtOutModulationCodeRate, 
                dvbtOutModulationConstellation, dvbtOutModulationGuardInterval, dvbtOutModulationFftMode, dvbtOutModulationChannelBandwidth, dvbtOutLocalizationCellId, 
                dvbtConfigurationDigitalMode, dvbtTestMode, dvbtStCellId, dvbtStTxDelayOffset, dvbtStTxFrequencyOffset
                 }
            STATUS current
            DESCRIPTION 
                "General DVB-T objects."
            ::= { rsXx9DvbtGroups 1 }

        
        dvbtNotifyBasic NOTIFICATION-GROUP
            NOTIFICATIONS { dvbtEncoderSummary, dvbtTest }
            STATUS current
            DESCRIPTION 
                "General DVB-T notifications."
            ::= { rsXx9DvbtGroups 101 }

        
        dvbtObjDvbH OBJECT-GROUP
            OBJECTS { dvbtModulationMpeFEC, dvbtModulationTimeSlicing, dvbtModulationInterleave, dvbtOutModulationMpeFEC, dvbtOutModulationTimeSlicing, 
                dvbtOutModulationInterleave }
            STATUS current
            DESCRIPTION 
                "Additional objects for DVB-H."
            ::= { rsXx9DvbtGroups 102 }

        
    
    END

--
-- RS-XX9-DVBT-MIB.mi2
--
