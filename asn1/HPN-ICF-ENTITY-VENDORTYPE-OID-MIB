-- =================================================================
-- Copyright (c) 2010-2014 Hewlett-Packard Development Company, L.P.
--
-- Description: The definition of Entity Vendortype OID
-- Reference:
-- Version: V4.64
-- History:
-- V1.0 2004.05.13  Created by lvzhenfeng, modified by gaolong.
-- V1.1 2004.05.22  Adjusted by gaolong and lvzhenfeng.
--   1. Adjust module name to hpnicfEntityVendorTypeOID and its location is set to { hpnicf 3 }.
--   2. Rename module name prefix from hpnicfevtModule to hpnicfevtModuleRt_
--   and hpnicfevtModuleSw_ for routers and switches seperately.
--   3. Add hpnicfevtSubModuleRouter and hpnicfevtSubModuleSwitch under hpnicfevtModule.
--   4. Split port type into two groups, one for routers, another for switches.
-- V1.11 2004-06-17 add hpnicfevtHotSwapFan node by limeng for garibaldi
-- V1.12 2004-07-19 add hpnicfevtModuleSwitchType {117-138}
-- V1.13 2004-07-29 add hpnicfevtPortSwitchType {50-58}
-- V1.14 2004-08-12 add hpnicfevtModuleSw_LSA1FP8U(hpnicfevtModuleSwitchType 139)
-- V1.15 2004-08-25 change enumeration name
--                     from hpnicfevtModuleSw_LS81SFCA(120) to hpnicfevtModuleSw_LS81SRPG0(120),
--                     from hpnicfevtModuleSw_LS81SFCB(121) to hpnicfevtModuleSw_LS81SRPG1(121),
--                     from hpnicfevtModuleSw_LS81SFCC(122) to hpnicfevtModuleSw_LS81SRPG2(122),
--                     from hpnicfevtModuleSw_LS81SFCD(123) to hpnicfevtModuleSw_LS81SRPG3(123).
--                  modify comments for these enumerations as well.
-- V1.2  2004-08-26 add sub identifier of hpnicfevtPortSwitchType from 59 to 71.
-- V1.21 2004-09-08 add sub identifier of hpnicfevtModuleSwitchType from 140 to 148.
-- V1.3  2004-09-14 add subidentifier under hpnicfevtModuleSwitchType from 149 to 157 by wangyahui
--                  add subidentifier under hpnicfevtModuleSwitchType from 158 to 159 by kangyinan
--                  add subidentifier under hpnicfevtModuleSwitchType from 72 to 93 by wangyahui
--                  add subidentifier under hpnicfevtModuleSwitchType from 94 to 96 by kangyinan
--                  add type description for hpnicfevtModuleSw_SP4, hpnicfevtModuleSw_UP1, hpnicfevtModuleSw_XP4 by kangyinan
-- V2.0  2004-10-12 updated by gaolong
--                  Change all underscore('_') characters to hyphen characters('-') because underscore character is not allowed in MIB module.
--                  Remove some adjacent hyphens
-- V2.1  2004-10-19 add subidentifier under hpnicfevtModuleSwitchType from 160 to 162 by kangyinan
--                  add subidentifier under hpnicfevtPortSwitchType 97 by kangyinan
-- V2.2  2004-09-18 add sub identifier for hpnicfevtModuleRouterType from 111 to 117 by taotao
-- V2.3  2004-11-18 add sub identifier 2 under hpnicfevtFan by liyutao
-- V2.4  2004-11-23 add subidentifier under hpnicfevtModuleSwitchType from 163 to 166 by zhangchengmei
-- V2.5  2004-12-04 add subidentifier 118 under hpnicfevtModuleRouterType by lizhiyong
-- V2.6  2004-12-23 add sub identifier 4 to 7 under hpnicfevtPowerSupply by Zhangjianfeng
--                  add sub identifier 167 to 169 under hpnicfevtModuleSwitchType by Zhangjianfeng
-- V2.7  2004-12-26 add subidentifier 170 under hpnicfevtModuleSwitchType by wangyahui
-- v2.8  2004-12-23 add subidentifier under hpnicfevtModuleSwitchType from 171 to 172 and
--                  add sub identifier 98 to 99 under hpnicfevtPortSwitchType by liyue
-- V2.9  2004-12-26 add sub identifier 173 under hpnicfevtModuleSwitchType by Zhangjianfeng
--                  add sub identifier 100 for 24G cascade port under hpnicfevtPort by Zhangjianfeng
-- V3.0  2004-01-07 add subidentifier 174 and 175 under hpnicfevtModuleSwitchType by wangyahui
-- V3.1  2005-01-31 add subidentifier 176 under hpnicfevtModuleSwitchType by wangyahui
-- V3.2  2005-02-26 add subidentifier 177 under hpnicfevtModuleSwitchType by zhangchengmei
--                  add subidentifier 101 to 137 under hpnicfevtPortSwitchType by zhangchengmei
--                  add subidentifier 178 under hpnicfevtModuleSwitchType by zhouqiang
--                  add subidentifier 138 under hpnicfevtPortSwitchType by zhouqiang
--                  add subidentifier 179 to 180 under hpnicfevtModuleSwitchType by wangyahui
--                  remove trailing spaces
-- V3.3  2005-03-22 add subidentifier 181 to 187 under hpnicfevtModuleSwitchType by zhangchengmei
-- V3.4  2004-12-29 add subidentifier 119 to 120 under hpnicfevtModuleRouterType by lizhiyong
-- V3.5  2005-04-12 add subidentifier 141 to 144 under hpnicfevtModuleRouterType by yinxiaoyu
--                  add subidentifier 30 to 33 under hpnicfevtPortRouterType by yinxiaoyu
-- V3.6  2005-04-07 add subidentifier 121 to 140 under hpnicfevtModuleRouterType by taotao
--                  change the name of subidentifier 118 under hpnicfevtModuleRouterType by taotao
--                  adjust file format
-- V3.7  2005-05-10 add subidentifier 188 to 216 under hpnicfevtModuleSwitchType by zhangchengmei
-- V3.8  2005-06-12 add subidentifier 145 to 149 under hpnicfevtModuleRouterType,
--                  add subidentifier 34 under hpnicfevtPortRouterType by wanghanlin
-- V3.9  2005-06-22 add subidentifier 150 under hpnicfevtModuleRouterType by yinxiaoyu
-- V4.0  2005-07-18 add subidentifier 217 to 219 under hpnicfevtModuleSwitchType by yangliming
--                  add subidentifier 139 to 142 under hpnicfevtPortSwitchType by wangyahui
-- V4.01 2005-07-29 add subidentifier 220 to 225 under hpnicfevtModuleSwitchType by wangyahui
-- V4.02 2005-07-21 change the name of subidentifier 183 under hpnicfevtModuleSwitchType,
--                  add subidentifier 226 to 227 under hpnicfevtModuleSwitchType by zhangchengmei
--       2005-08-29 add subidentifier 143 under hpnicfevtPortSwitchType by qianxiaoyu
--                  add subidentifier 151 to 161 under hpnicfevtModuleRouterType by taotao
--                  add subidentifier 35 to 41 under hpnicfevtPortRouterType by taotao
-- V4.03 2005-09-07 add hpnicfevtCPU and hpnicfevtGeneralCPU by taotao
--                  add subidentifier 162 to 163 under hpnicfevtModuleRouterType by taotao
--                  adjust file format by gaolong
-- V4.04 2005-09-13 add subidentifier 228 to 253 under hpnicfevtModuleSwitchType by zhangchengmei
--       2005-09-13 add subidentifier 257 to 268 under hpnicfevtModuleSwitchType by zhangchengmei
-- V4.05 2005-11-04 add subidentifier 144 to 149 under hpnicfevtPortSwitchType by zhangchengmei
--                  add subidentifier 150 under hpnicfevtPortSwitchType by huangyuetao
--                  add subidentifier 269 to 271 under hpnicfevtModuleSwitchType by yangxiaopeng
--                  add subidentifier 272 under hpnicfevtModuleSwitchType by qianxiaoyu
--                  add subidentifier 164 to 165 under hpnicfevtModuleRouterType by xuejiayong
-- V4.06 2005-11-24 add subidentifier 500 to 501 under hpnicfevtModuleSwitchType by wangyahui
-- V4.07 2005-11-28 add subidentifier 300 to 316 under hpnicfevtModuleSwitchType by zhangchengmei
-- V4.08 2005-12-09 add subidentifier 220 to 223 under hpnicfevtModuleRouterType by taotao
-- V4.09 2005-12-30 add subidentifier 151 to 170 under hpnicfevtPortSwitchType by zhangchengmei
-- V4.10 2006-01-04 add subidentifier 701 under hpnicfevtModuleSwitchType by qianxiaoyu
-- V4.11 2006-02-12 add subidentifier 200 to 219 under hpnicfevtModuleRouterType by liutinghai
--                  add subidentifier 702 under hpnicfevtModuleSwitchType by chenxiaohui
--                  add subidentifier 600 under hpnicfevtModuleRouterType by qujin
--                  add subidentifier 317 under hpnicfevtModuleSwitchType by zhangchengmei
-- V4.12 2006-02-24 add subidentifier 703 under hpnicfevtModuleSwitchType by chijuntao
--                  add subidentifier 224 to 228 under hpnicfevtModuleRouterType by taotao
-- V4.13 2006-02-27 add subidentifier 171 to 174 under hpnicfevtPortSwitchType by wangshunli
--                  add subidentifier 318 to 336 under hpnicfevtModuleSwitchType by zhaiyingying
-- V4.14 2006-03-14 add subidentifier 175 under hpnicfevtPortSwitchType by wangyahui
--                  add subidentifier 502 to 504 under hpnicfevtModuleSwitchType by wangyahui
-- V4.15 2006-04-03 add subidentifier 176 under hpnicfevtPortSwitchType by wangyahui
-- V4.16 2006-04-26 add subidentifier 229 to 233 under hpnicfevtModuleRouterType by taotao
-- V4.17 2006-04-21 add subidentifier 337 to 340 under hpnicfevtModuleSwitchType by zhaiyingying
-- V4.18 2006-06-05 add subidentifier 704 to 705 under hpnicfevtModuleSwitchType by zhangxianguo
--                  add subidentifier 505 to 506 under hpnicfevtModuleSwitchType by zhangjianfeng
--                  add subidentifier 341 to 349 under hpnicfevtModuleSwitchType by zhaiyingying
--                  add subidentifier 177 to 178 under hpnicfevtPortSwitchType by zhangjianfeng
--                  add subidentifier 179 to 180 under hpnicfevtPortSwitchType by zhangxianguo
-- V4.19 2006-08-23 add subidentifier 507 to 509 under hpnicfevtModuleSwitchType by wangyahui
--                  modify object name of subidentifier 502 and 503 under hpnicfevtModuleSwitchType by wangyahui
--                  add subidentifier 234 to 235 under hpnicfevtModuleRouterType by liutinghai
--                  add subidentifier 350 to 357 under hpnicfevtModuleSwitchType by zhaiyingying
-- V4.20 2006-09-26 add subidentifier 510 to 514 under hpnicfevtModuleSwitchType by wangyahui
--                  add subidentifier 601 to 603 under hpnicfevtModuleRouterType by zhoujianming
--                  add subidentifier 236 to 239 under hpnicfevtModuleRouterType by qikai
--                  add subidentifier 240 to 241 under hpnicfevtModuleRouterType by liutinghai
--                  add subidentifier 800 to 801 under hpnicfevtModuleSwitchType by luoguixing
-- V4.21 2006-10-26 add subidentifier 358 to 370 under hpnicfevtModuleSwitchType by zhaiyingying
--                  add subidentifier 183 under hpnicfevtPortSwitchType by zhaiyingying
--                  add subidentifier 515 to 526 under hpnicfevtModuleSwitchType by wangyahui
--                  add subidentifier 181 to 182 under hpnicfevtPortSwitchType by wangyahui
-- V4.22 2006-11-02 add subidentifier 527 to 536 under hpnicfevtModuleSwitchType by wangyahui
--                  modify description of 511 to 513 under hpnicfevtModuleSwitchType by wangyahui
--       2006-11-10 add subidentifier 371 to 378 under hpnicfevtModuleSwitchType by shuxiongtao
--       2006-11-08 add subidentifier 184 to 185 under hpnicfevtPortSwitchType by zhaiyingying
-- V4.23 2006-12-04 add subidentifier 242 to 243 under hpnicfevtModuleRouterType by liutinghai
-- V4.24 2006-01-24 add subidentifier 244 to 245 under hpnicfevtModuleRouterType by liutinghai
-- V4.25 2007-03-19 add subidentifier 537 under hpnicfevtModuleSwitchType by wangyahui
-- V4.26 2007-04-12 add subidentifier 538 to 542 under hpnicfevtModuleSwitchType by wangyahui
-- V4.27 2007-04-25 add subidentifier 706 under hpnicfevtModuleSwitchType by zhangzongyi
--                  add subidentifier 379 to 380 under hpnicfevtModuleSwitchType by zhaiyingying
--                  add subidentifier 246 to 250 under hpnicfevtModuleRouterType by liutinghai
--                  add subidentifier 42 under hpnicfevtPortRouterType by liutinghai
-- V4.28 2007-05-28 add subidentifier 707 under hpnicfevtModuleSwitchType by ligaoxu
--                  add subidentifier 381 to 392 under hpnicfevtModuleSwitchType by shuxiongtao
--                  modify name of subidentifier 371 and 374 under hpnicfevtModuleSwitchType by shuxiongtao
--                  add subidentifier 251 to 253 under hpnicfevtModuleRouterType by qikai
--                  add subidentifier 254 to 255 under hpnicfevtModuleRouterType by liutinghai
--                  add subidentifier 186 under hpnicfevtPortSwitchType by jinzhaoqiong
-- V4.29 2007-07-09 add subidentifier 543 to 551 under hpnicfevtModuleSwitchType by zhangjianfeng
--                  add subidentifier 552 to 554 under hpnicfevtModuleSwitchType by wangyahui
-- V4.30 2007-07-26 add subidentifier 400 under hpnicfevtModuleRouterType by xuejiayong
--                  add subidentifier 708 under hpnicfevtModuleSwitchType by xiuyihong
--                  add subidentifier 256 to 258 under hpnicfevtModuleRouterType by qikai
--                  add subidentifier 259 to 263 under hpnicfevtModuleRouterType by liutinghai
--                  add subidentifier 3 to 5 under hpnicfevtOther by gaolong
-- V4.31 2007-08-27 add subidentifier 187 to 188 under hpnicfevtPortSwitchType by ruanhan
--                  add subidentifier 802 to 804 under hpnicfevtModuleSwitchType by luoguixing
--                  add subidentifier 393 to 397 under hpnicfevtModuleSwitchType by shuxiongtao
-- V4.32 2007-09-25 add subidentifier 555 to 559 under hpnicfevtModuleSwitchType by wangyahui
--                  add subidentifier 805 under hpnicfevtModuleSwitchType by luoguixing
--                  add subidentifier 401 to 403 under hpnicfevtModuleRouterType by tanwen
--                  add subidentifier 43 under hpnicfevtPortRouterType by qikai
--                  add subidentifier 266 to 267 under hpnicfevtModuleRouterType by qikai
--                  add subidentifier 398 to 399 under hpnicfevtModuleSwitchType by hexuefei
-- V4.33 2007-10-22 add subidentifier 189 under hpnicfevtPortSwitchType by liaoxin
--                  add subidentifier 268 under hpnicfevtModuleRouterType by liutinghai
-- V4.34 2007-11-26 add subidentifier 269 to 273 under hpnicfevtModuleRouterType by liutinghai
--                  add subidentifier 274 to 276 under hpnicfevtModuleRouterType by qikai
--                  add subidentifier 404 to 406 under hpnicfevtModuleRouterType by chaiyaqin
--                  add subidentifier 400 to 407 under hpnicfevtModuleSwitchType by shuxiongtao
-- V4.35 2007-12-27 add subidentifier 277 to 278 under hpnicfevtModuleRouterType by liutinghai
--                  add subidentifier 560 to 568 under hpnicfevtModuleSwitchType by wangyahui
-- V4.36 2008-01-30 add subidentifier 408 under hpnicfevtModuleSwitchType by hexuefei
--                  add subidentifier 569 to 572 under hpnicfevtModuleSwitchType by wangyahui
--                  add subidentifier 279 to 280 under hpnicfevtModuleRouterType by qikai
--                  add subidentifier 190 under hpnicfevtPortSwitchType by liujingya
-- V4.37 2008-02-20 add subidentifier 720 to 724 under hpnicfevtModuleSwitchType by chaiyaqin
--                  add subidentifier 573 to 574 under hpnicfevtModuleSwitchType by zhangjianfeng
--                  modify name of subidentifier 546 and 550 under hpnicfevtModuleSwitchType by zhangjianfeng
--                  add subidentifier 575 to 576 under hpnicfevtModuleSwitchType by wangyahui
--                  add subidentifier 281 under hpnicfevtModuleRouterType by liutinghai
-- V4.38 2008-03-31 add subidentifier 806 to 808 under hpnicfevtModuleSwitchType by luoguixing
--                  add subidentifier 709 to 715 under hpnicfevtModuleSwitchType by wangcong
--                  add subidentifier 191 to 196 under hpnicfevtPortSwitchType by wangcong
--                  add subidentifier 44 under hpnicfevtPortRouterType by liutinghai
--                  add subidentifier 409 to 431 under hpnicfevtModuleSwitchType by zhaiyingying
--                  add subidentifier 432 under hpnicfevtModuleSwitchType by shuxiongtao
-- V4.39 2008-04-29 add subidentifier 577 to 589 under hpnicfevtModuleSwitchType by wangyahui
--                  add subidentifier 407 to 409 under hpnicfevtModuleRouterType by tanwen
-- V4.40 2008-05-31 add subidentifier 410 to 413 under hpnicfevtModuleRouterType by tanwen
--                  add subidentifier 282 to 284 under hpnicfevtModuleRouterType by qikai
--                  add subidentifier 285 to 286 under hpnicfevtModuleRouterType by liutinghai
-- V4.41 2008-07-28 add subidentifier 590 to 592 under hpnicfevtModuleSwitchType by wangyahui
--                  add subidentifier 287 to 289 under hpnicfevtModuleRouterType by qikai
--                  add subidentifier 290 to 291 under hpnicfevtModuleRouterType by liutinghai
--                  add subidentifier 45 to 46 under hpnicfevtPortRouterType by liutinghai
--                  add subidentifier 809 to 810 under hpnicfevtModuleSwitchType by luoguixing
-- V4.42 2008-08-26 modify name of 379 and 399 under hpnicfevtModuleSwitchType by wangwei
--                  modify description of 408 under hpnicfevtModuleSwitchType by wangwei
--                  modify name and description of 804 under hpnicfevtModuleSwitchType by wangwei
--                  add subidentifier 433 to 434 under hpnicfevtModuleSwitchType by wangwei
--                  add subidentifier 593 to 595 under hpnicfevtModuleSwitchType by wangyahui
--                  modify name and description of 256 and 288 under hpnicfevtPortRouterType by qikai
--                  add subidentifier 292 to 293 under hpnicfevtPortRouterType by qikai
-- V4.43 2008-10-13 add subidentifier 725 under hpnicfevtModuleSwitchType by ruanhan
--                  add subidentifier 197 under hpnicfevtPortSwitchType by ruanhan
--                  add subidentifier 811 under hpnicfevtModuleSwitchType by luoguixing
--                  add subidentifier 596 to 601 under hpnicfevtModuleSwitchType by wangyahui
-- V4.44 2008-11-04 add subidentifier 294 under hpnicfevtPortRouterType by qikai
--                  add subidentifier 414 under hpnicfevtModuleRouterType by tanwen
-- V4.45 2008-12-01 add subidentifier 602 to 619 under hpnicfevtModuleSwitchType by wangyahui
--                  add subidentifier 435 to 442 under hpnicfevtModuleSwitchType by zhaiyingying
--                  modify name of 546 under hpnicfevtModuleSwitchType by zhangjianfeng
--                  add subidentifier 295 under hpnicfevtPortRouterType by qikai
--                  add subidentifier 443 under hpnicfevtModuleSwitchType by shuxiongtao
-- V4.46 2008-12-25 add subidentifier 620 to 622 under hpnicfevtModuleSwitchType by wangyahui
--                  add subidentifier 716 to 718 under hpnicfevtModuleSwitchType by zhangshilin
--                  add subidentifier 444 to 445 under hpnicfevtModuleSwitchType by wangchang
-- V4.47 2009-03-02 add subidentifier 446 to 452 under hpnicfevtModuleSwitchType by wangchang
--                  add subidentifier 719 under hpnicfevtModuleSwitchType by zhangshilin
--                  add subidentifier 623 to 633 under hpnicfevtModuleSwitchType by wangyahui
-- V4.48 2009-03-31 add subidentifier 415 under hpnicfevtModuleRouterType by tanwen
--                  add subidentifier 296 under hpnicfevtPortRouterType by qikai
--                  add subidentifier 297 to 298 under hpnicfevtPortRouterType by qianjialin
--                  add subidentifier 453 to 464 under hpnicfevtModuleSwitchType by huyinxing
-- V4.49 2009-07-02 add subidentifier 299 to 302 under hpnicfevtModuleRouterType by qikai
--                  add subidentifier 303 under hpnicfevtModuleRouterType by chenfeihu
--                  add subidentifier 304 to 307 under hpnicfevtModuleRouterType by qianjialin
--                  add subidentifier 634 to 637 under hpnicfevtModuleSwitchType by wangyahui
--                  add subidentifier 604 to 606 under hpnicfevtModuleRouterType by chenjianhui
--                  add subidentifier 465 to 468 under hpnicfevtModuleSwitchType by zhaiyingying
--                  add subidentifier 469 to 472 under hpnicfevtModuleSwitchType by huyinxing
--                  add subidentifier 198 under hpnicfevtPortSwitchType by huyinxing
--                  add subidentifier 199 under hpnicfevtPortSwitchType by zhangjianfeng
-- V4.50 2009-08-28 add subidentifier 638 to 640 under hpnicfevtModuleSwitchType by wangyahui
--                  add subidentifier 308 to 310 under hpnicfevtModuleRouterType by qianjialin
-- V4.51 2009-11-09 add subidentifier 726 under hpnicfevtModuleSwitchType by ruanhan
--                  add subidentifier 641 under hpnicfevtModuleSwitchType by wangyahui
--                  add subidentifier 473 to 477 under hpnicfevtModuleSwitchType by yudongyang
--                  add subidentifier 478 to 485 under hpnicfevtModuleSwitchType by heweibin
-- V4.52 2009-12-31 add subidentifier 200 to 201 under hpnicfevtPortSwitchType by zhanghaiyang
--                  add subidentifier 642 to 651 under hpnicfevtModuleSwitchType by wangyahui
--                  add subidentifier 416 under hpnicfevtModuleRouterType by lixiaomin
--                  add subidentifier 486 under hpnicfevtModuleSwitchType by yudongyang
--                  add subidentifier 727 to 728 under hpnicfevtModuleSwitchType by xiaobing
--                  add subidentifier 652 to 659 under hpnicfevtModuleSwitchType by wangyahui
--                  add subidentifier 487 to 488 under hpnicfevtModuleSwitchType by huyinxing
--                  add subidentifier 660 to 662 under hpnicfevtModuleSwitchType by wangyahui
--                  add subidentifier 202 to 203 under hpnicfevtPortSwitchType by yangdonghong
-- V4.53 2010-03-03 add subidentifier 812 under hpnicfevtModuleSwitchType by mashuhang
--                  add subidentifier 489 to 497 under hpnicfevtModuleSwitchType by liubuxiang
--                  add subidentifier 498 to 499 under hpnicfevtModuleSwitchType by shikejun
--                  add subidentifier 900 under hpnicfevtModuleSwitchType by yangqiulin
--                  add subidentifier 901 to 902 under hpnicfevtModuleSwitchType by huyinxing
-- V4.54 2010-04-21 add subidentifier 903 to 904 under hpnicfevtModuleSwitchType by huyinxing
--                  add subidentifier 905 to 907 under hpnicfevtModuleSwitchType by shikejun
--                  add subidentifier 663 to 685 under hpnicfevtModuleSwitchType by wangyahui
--                  add subidentifier 813 under hpnicfevtModuleSwitchType by mashuhang
--                  add subidentifier 729 under hpnicfevtModuleSwitchType by zhangshilin
--                  add subidentifier 908 to 913 under hpnicfevtModuleSwitchType by yangbin
--                  add subidentifier 914 to 918 under hpnicfevtModuleSwitchType by huyinxing
--                  add subidentifier 5000 to 5011 under hpnicfevtModuleRouterType by qianjialin
--                  add subidentifier 919 to 927 under hpnicfevtModuleSwitchType by langgaoyi
-- V4.55 2011-01-31 add subidentifier 417 under hpnicfevtModuleRouterType by tanwen
--                  add subidentifier 311 to 314 under hpnicfevtModuleRouterType by qianjialin
--                  add subidentifier 686 to 691 under hpnicfevtModuleSwitchType by wangyahui
--                  add subidentifier 928 to 929 under hpnicfevtModuleSwitchType by langgaoyi
-- V4.56 2011-04-22 add subidentifier 930 under hpnicfevtModuleSwitchType by liuhui
--                  add subidentifier 814 to 815 under hpnicfevtModuleSwitchType by mashuhang
--                  add subidentifier 692 to 694 under hpnicfevtModuleSwitchType by wangyahui
--                  add subidentifier 204 under hpnicfevtPortSwitchType by yangliming
-- V4.57 2011-06-30 add subidentifier 695, 1201 to 1211 under hpnicfevtModuleSwitchType by wangyahui
--                  add subidentifier 205 to 207 under hpnicfevtPortSwitchType by gaoruichang
-- V4.58 2011-08-31 add subidentifier 696 to 697 under hpnicfevtModuleSwitchType by langgaoyi
--                  add subidentifier 208 under hpnicfevtPortSwitchType by wangshunli
--                  add subidentifier 931 to 933 under hpnicfevtModuleSwitchType by langgaoyi
--                  add subidentifier 934 under hpnicfevtModuleSwitchType by zhaohonghai
-- V4.59 2012-04-20 add subidentifier 935 to 938, 942 under hpnicfevtModuleSwitchType by wangjiangnan
--                  add subidentifier 1212 to 1218 under hpnicfevtModuleSwitchType by wangyahui
--                  add subidentifier 939 to 941 under hpnicfevtModuleSwitchType by herui
--                  modify name of 205 to 207 under hpnicfevtPortSwitchType by xvman
--                  add subidentifier 350 to 360 under hpnicfevtModuleRouterType by chenfeihu
--                  add subidentifier 943 to 945 under hpnicfevtModuleSwitchType by langgaoyi
--                  add subidentifier 209, 211 under hpnicfevtPortSwitchType by wangyahui
--                  add subidentifier 730 to 731 under hpnicfevtModuleSwitchType by panxiyuan
--                  add subidentifier 210 under hpnicfevtPortSwitchType by panxiyuan
--                  add subidentifier 315 to 349 under hpnicfevtModuleRouterType by qianjialin
--                  add subidentifier 946 to 948 under hpnicfevtModuleSwitchType by zhangheng
--                  add subidentifier 949 to 956 under hpnicfevtModuleSwitchType by zhengjiang
--                  add subidentifier 957 under hpnicfevtModuleSwitchType by zhaohonghai
--                  add subidentifier 361 to 372 under hpnicfevtModuleRouterType by qianjialin
--                  add subidentifier 212 under hpnicfevtPortSwitchType by wangyahui
--                  add subidentifier 732 under hpnicfevtModuleSwitchType by houchengshuai
--                  add subidentifier 1219 to 1230 under hpnicfevtModuleSwitchType by wangyahui
-- V4.60 2013-01-07 add subidentifier 733 under hpnicfevtModuleSwitchType by shixuemei
--                  add subidentifier 958 to 959 under hhpnicfevtModuleSwitchType by zhaohonghai
--                  add subidentifier 960 to 965, 996 under hpnicfevtModuleSwitchType by zhangheng
--                  add subidentifier 966 to 988 under hpnicfevtModuleSwitchType by yebiaoxiang
--                  add subidentifier 989 to 995 under hpnicfevtModuleSwitchType by zhaohonghai
--                  add subidentifier 1231 to 1255 under hpnicfevtModuleSwitchType by wangyahui
--                  add subidentifier 373 to 388 under hpnicfevtModuleRouterType by qianjialin
--                  add subidentifier 1400 to 1410 under hpnicfevtModuleSwitchType by qizhenglin
--                  add subidentifier 213 to 219 under hpnicfevtPortSwitchType by yebiaoxiang
--                  add subidentifier 47 under hpnicfevtPortRouterType by qianjialin
--                  add subidentifier 418 under hpnicfevtModuleRouterType by tanwen
--                  modify name of 673, 1214, 1215 under hpnicfevtModuleSwitchType by wangyahui
-- V4.61 2013-04-26 add subidentifier 1256 to 1269 under hpnicfevtModuleSwitchType by wangyahui
--                  add subidentifier 607 to 610 under hpnicfevtModuleRouterType by jiangwendong
--                  add subidentifier 220 to 222 under hpnicfevtPortSwitchType by jiangyongjiang
--                  add subidentifier 389 to 392 under hpnicfevtModuleRouterType by chenfeihu
--                  add subidentifier 393 to 398 under hpnicfevtModuleRouterType by qianjialin
--                  modify name of 975 to 982 under hpnicfevtModuleSwitchType by lihaijun
--                  add subidentifier 997 to 1015 under hpnicfevtModuleSwitchType by chenke
--                  add subidentifier 1016 to 1018 under hpnicfevtModuleSwitchType by jiangyongjiang
--                  add subidentifier 1270 to 1273 under hpnicfevtModuleSwitchType by sunzhenxing
--                  add subidentifier 1 to 8 under hpnicfevtModuleCommonCards by zhouxiaodong
-- V4.62 2013-10-10 add subidentifier 419 to 431 under hpnicfevtModuleRouterType by tanwen
--                  add subidentifier 611 under hpnicfevtModuleRouterType by jiangwendong
--                  add subidentifier 399, 800 to 804, 807 under hpnicfevtModuleRouterType by qianjialin
--                  add subidentifier 805 to 806 under hpnicfevtModuleRouterType by chenfeihu
--                  add subidentifier 1274 to 1279, 1293 to 1296 under hpnicfevtModuleSwitchType by lihaijun
--                  add subidentifier 1019 to 1024 under hpnicfevtModuleSwitchType by zhaohonghai
--                  add subidentifier 1280 to 1287, 1298 to 1306 under hpnicfevtModuleSwitchType by sunzhenxing
--                  add subidentifier 1025, 1028, 1029, 1050 under hpnicfevtModuleSwitchType by jiangyongjiang
--                  add subidentifier 1026 to 1027, 1030 to 1049 under hpnicfevtModuleSwitchType by chenke
--                  add subidentifier 816 under hpnicfevtModuleSwitchType by luoguixing
--                  add subidentifier 1288 to 1292, 1297 under hpnicfevtModuleSwitchType by wujili
--                  modify name of 1234 to 1236 under hpnicfevtModuleSwitchType by lihaijun
--                  add subidentifier 48 to 49 under hpnicfevtPortRouterType by jiangwendong
--                  add subidentifier 223 to 224 under hpnicfevtPortSwitchType by jiangyongjiang
-- V4.63 2014-01-26 add subidentifier 432 under hpnicfevtModuleRouterType by zhaowenbin
--                  add subidentifier 808 to 809, 814 under hpnicfevtModuleRouterType by qianjialin
--                  add subidentifier 810 to 813, 815 to 817 under hpnicfevtModuleRouterType by chenfeihu
--                  add subidentifier 734 to 739 under hpnicfevtModuleSwitchType by panxiyuan
--                  modify name of 1032 to 1041 under hpnicfevtModuleSwitchType by chenke
--                  add subidentifier 1051 to 1055 under hpnicfevtModuleSwitchType by zhaohonghai
--                  add subidentifier 1056 to 1058 under hpnicfevtModuleSwitchType by chenke
--                  add subidentifier 1307 to 1313 under hpnicfevtModuleSwitchType by wujili
--                  add subidentifier 1314 to 1316 under hpnicfevtModuleSwitchType by lihaijun
--                  add subidentifier 1317 to 1319 under hpnicfevtModuleSwitchType by sunzhenxing
--                  add subidentifier 1320 to 1326 under hpnicfevtModuleSwitchType by jiangyongjiang
-- V4.64 2014-04-25 add subidentifier 1059 to 1069 under hpnicfevtPortSwitchType by youhua
--                  add subidentifier 1070 to 1102 under hpnicfevtModuleSwitchType by chenke
--                  add subidentifier 1103 to 1107 under hpnicfevtModuleSwitchType by lihaijun
--                  add subidentifier 1108 under hpnicfevtModuleSwitchType by zhaohonghai
--                  add subidentifier 1327 to 1328 under hpnicfevtModuleSwitchType by sunzhenxing
--                  add subidentifier 1329 to 1331 under hpnicfevtModuleSwitchType by lihaijun
--                  add subidentifier 1332 to 1371 under hpnicfevtModuleSwitchType by jiangyongjiang
--                  add subidentifier 1372 to 1373 under hpnicfevtModuleSwitchType by sunzhenxing
--                  modify name of 733 under hpnicfevtModuleSwitchType by maoyun
--                  add subidentifier 740 to 743 hpnicfevtModuleSwitchType by tanxiaopeng
--                  add subidentifier 433 under hpnicfevtModuleRouterType by zhaowenbin
--                  add subidentifier 818 to 822, 824 to 825 under hpnicfevtModuleRouterType by chenfeihu
--                  add subidentifier 823 under hpnicfevtModuleRouterType by qianjialin
--                  add subidentifier 50 to 51 under hpnicfevtPortRouterType by chenfeihu
--                  add subidentifier 225 to 232 under hpnicfevtPortSwitchType by pantao
--                  modify name of 1400, remove 1401 to 1410 under hpnicfevtModuleSwitchType by qizhenglin
-- =================================================================
HPN-ICF-ENTITY-VENDORTYPE-OID-MIB DEFINITIONS ::= BEGIN

IMPORTS
    MODULE-IDENTITY
        FROM SNMPv2-SMI
    hpnicf
        FROM HPN-ICF-OID-MIB;


hpnicfEntityVendorTypeOID MODULE-IDENTITY

        LAST-UPDATED "200903310000Z"
        ORGANIZATION
            ""
        CONTACT-INFO
            ""
        DESCRIPTION
            "The private MIB includes the definition of the object
            identifiers on products, which are used by the
            entPhysicalTable of the ENTITY-MIB to uniquely identify the
            type of each physical entry."
        ::= { hpnicf 3 }


hpnicfEntityVendortypeObjects   OBJECT IDENTIFIER ::= { hpnicfEntityVendorTypeOID 1 }

-- This MIB assigns OIDs for use as the values of entPhysicalVendorType.
-- The subtrees in which the OID values are assigned, are structured
-- into a hierarchy based on the values of RFC 2037's PhysicalClass
-- textual convention.  For reference, the definition of PhysicalClass
-- is as follows:
--
--      PhysicalClass ::= TEXTUAL-CONVENTION
--      STATUS          current
--      DESCRIPTION
--             "An enumerated value which provides an indication of the
--              general hardware type of a particular physical entity."
--      SYNTAX      INTEGER  {
--              other(1),
--              unknown(2),
--              chassis(3),
--              backplane(4),
--              container(5),    e.g. slot or daughter-card holder
--              powerSupply(6),
--              fan(7),
--              sensor(8),
--              module(9),       e.g. plug-in card or daughter-card
--              port(10),
--              stack(11)        e.g., stack of multiple chassis entities
--          }
--

hpnicfevtOther     OBJECT IDENTIFIER ::= { hpnicfEntityVendortypeObjects 1 }

-- May be defined detailed in future.

hpnicfevtOtherUnknownCard  OBJECT IDENTIFIER ::= { hpnicfevtOther 1 }
hpnicfevtCPU               OBJECT IDENTIFIER ::= { hpnicfevtOther 2 }
hpnicfevtDOM               OBJECT IDENTIFIER ::= { hpnicfevtOther 3 }  -- Disk on Module
hpnicfevtCFCard            OBJECT IDENTIFIER ::= { hpnicfevtOther 4 }  -- Compact Flash Card
hpnicfevtHardDisk          OBJECT IDENTIFIER ::= { hpnicfevtOther 5 }  -- Hard Disk

-- hpnicfevtGeneralCPU is a general vendor type of CPU.  It is used only for
-- general purpose.  It is strongly recommended that this object should not
-- be used to present the specific CPU vendor type in most cases.  More
-- accurate and clear vendor types should be defined to present specific CPU.
hpnicfevtGeneralCPU        OBJECT IDENTIFIER ::= { hpnicfevtCPU 1 }


hpnicfevtUnknown   OBJECT IDENTIFIER ::= { hpnicfEntityVendortypeObjects 2 }

hpnicfevtChassis   OBJECT IDENTIFIER ::= { hpnicfEntityVendortypeObjects 3 }

-- chassis OID assignments
-- May be substituted by sysObjectID.  So none is assigned at present.

--
-- backplane
--   The enumeration 'backplane' is applicable if the physical
--   entity class is some sort of device for aggregating and
--   forwarding networking traffic, such as a shared backplane in
--   a modular ethernet switch.  Note that an agent may model a
--   backplane as a single physical entity, which is actually
--   implemented as multiple discrete physical components (within
--   a chassis or stack).
--

hpnicfevtBackplane     OBJECT IDENTIFIER ::= { hpnicfEntityVendortypeObjects 4 }

--
-- hpnicfevtContainer section:
--
hpnicfevtContainer     OBJECT IDENTIFIER ::= { hpnicfEntityVendortypeObjects 5 }

--
-- hpnicfevtPowerSupply section:
--
hpnicfevtPowerSupply   OBJECT IDENTIFIER ::= { hpnicfEntityVendortypeObjects 6 }
hpnicfevtPowerSupplyAC         OBJECT IDENTIFIER ::= { hpnicfevtPowerSupply 2 }
hpnicfevtPowerSupplyDC         OBJECT IDENTIFIER ::= { hpnicfevtPowerSupply 3 }
hpnicfevtPowerSupplySTD130W    OBJECT IDENTIFIER ::= { hpnicfevtPowerSupply 4 }     -- Standard 130W PSU
hpnicfevtPowerSupplySTD180W    OBJECT IDENTIFIER ::= { hpnicfevtPowerSupply 5 }     -- Standard 180W PSU
hpnicfevtPowerSupplyPOE24Port  OBJECT IDENTIFIER ::= { hpnicfevtPowerSupply 6 }     -- 24 Port POE PSU 480W
hpnicfevtPowerSupplyPOE48Port  OBJECT IDENTIFIER ::= { hpnicfevtPowerSupply 7 }     -- 48 Port POE PSU 480W

--
-- hpnicfevtFan section:
--
hpnicfevtFan       OBJECT IDENTIFIER ::= { hpnicfEntityVendortypeObjects 7 }
hpnicfevtHotSwapFan        OBJECT IDENTIFIER ::=  { hpnicfevtFan 1 }
hpnicfevtNonHotSwapFan     OBJECT IDENTIFIER ::=  { hpnicfevtFan 2 }

--
-- hpnicfevtSensor section:
--
hpnicfevtSensor        OBJECT IDENTIFIER ::= { hpnicfEntityVendortypeObjects 8 }
hpnicfevtSensorTemperature     OBJECT IDENTIFIER ::= { hpnicfevtSensor 1 }
hpnicfevtSensorVoltage         OBJECT IDENTIFIER ::= { hpnicfevtSensor 2 }
hpnicfevtSensorFanSpeed        OBJECT IDENTIFIER ::= { hpnicfevtSensor 3 }


--
-- hpnicfevtModule section:
--
hpnicfevtModule        OBJECT IDENTIFIER ::= { hpnicfEntityVendortypeObjects 9 }

-- hpnicfevtModule is subdivided into sections like Router and Switch. These represent
-- cards used only on the router and switch.
-- hpnicfevtModuleCommonCards contains cards that can be used interchangeably
-- across more than one platform


-- Acronyms used in the hpnicfevtModule section:
--

hpnicfevtModuleUnknownCard     OBJECT IDENTIFIER ::= { hpnicfevtModule 1 }

-- hpnicfevtModuleCommonCards - cards and subcards common to more
-- than one platform
hpnicfevtModuleCommonCards     OBJECT IDENTIFIER ::= { hpnicfevtModule 2 }

hpnicfevtModuleBoxCEN                         OBJECT IDENTIFIER ::= { hpnicfevtModuleCommonCards 1 }
hpnicfevtModuleBoxIRF48GE                     OBJECT IDENTIFIER ::= { hpnicfevtModuleCommonCards 2 }
hpnicfevtModuleBoxIRF24GE24TGE                OBJECT IDENTIFIER ::= { hpnicfevtModuleCommonCards 3 }
hpnicfevtModuleChassisMpu                     OBJECT IDENTIFIER ::= { hpnicfevtModuleCommonCards 4 }
hpnicfevtModuleLPU48GE                        OBJECT IDENTIFIER ::= { hpnicfevtModuleCommonCards 5 }
hpnicfevtModuleLPU4GE4Serial                  OBJECT IDENTIFIER ::= { hpnicfevtModuleCommonCards 6 }
hpnicfevtModuleLPU4GE4Pos                     OBJECT IDENTIFIER ::= { hpnicfevtModuleCommonCards 7 }
hpnicfevtModuleLPU4GE4E1                      OBJECT IDENTIFIER ::= { hpnicfevtModuleCommonCards 8 }


-- hpnicfevtModuleRouterType cards are slot-cards specific to the Router.
hpnicfevtModuleRouterType      OBJECT IDENTIFIER ::= { hpnicfevtModule 3 }

--hpnicfevtModuleRt-Unavailable               OBJECT IDENTIFIER ::= { hpnicfevtModuleRouterType 1 }
hpnicfevtModuleRt-As                          OBJECT IDENTIFIER ::= { hpnicfevtModuleRouterType 2 }
hpnicfevtModuleRt-Sa                          OBJECT IDENTIFIER ::= { hpnicfevtModuleRouterType 3 }
hpnicfevtModuleRt-Bi                          OBJECT IDENTIFIER ::= { hpnicfevtModuleRouterType 4 }
hpnicfevtModuleRt-E12                         OBJECT IDENTIFIER ::= { hpnicfevtModuleRouterType 5 }
hpnicfevtModuleRt-E14                         OBJECT IDENTIFIER ::= { hpnicfevtModuleRouterType 6 }
hpnicfevtModuleRt-Fe1                         OBJECT IDENTIFIER ::= { hpnicfevtModuleRouterType 7 }
hpnicfevtModuleRt-E1                          OBJECT IDENTIFIER ::= { hpnicfevtModuleRouterType 8 }
hpnicfevtModuleRt-Fe2                         OBJECT IDENTIFIER ::= { hpnicfevtModuleRouterType 9 }
hpnicfevtModuleRt-Vi2                         OBJECT IDENTIFIER ::= { hpnicfevtModuleRouterType 11 }
hpnicfevtModuleRt-Vi4                         OBJECT IDENTIFIER ::= { hpnicfevtModuleRouterType 12 }
hpnicfevtModuleRt-Vi30                        OBJECT IDENTIFIER ::= { hpnicfevtModuleRouterType 13 }
hpnicfevtModuleRt-S1b                         OBJECT IDENTIFIER ::= { hpnicfevtModuleRouterType 14 }
hpnicfevtModuleRt-Sa2                         OBJECT IDENTIFIER ::= { hpnicfevtModuleRouterType 15 }
hpnicfevtModuleRt-As16                        OBJECT IDENTIFIER ::= { hpnicfevtModuleRouterType 16 }
hpnicfevtModuleRt-New8as                      OBJECT IDENTIFIER ::= { hpnicfevtModuleRouterType 17 }
hpnicfevtModuleRt-Sa1                         OBJECT IDENTIFIER ::= { hpnicfevtModuleRouterType 18 }
hpnicfevtModuleRt-Fxs2                        OBJECT IDENTIFIER ::= { hpnicfevtModuleRouterType 19 }
hpnicfevtModuleRt-Fxo2                        OBJECT IDENTIFIER ::= { hpnicfevtModuleRouterType 20 }
hpnicfevtModuleRt-Em2                         OBJECT IDENTIFIER ::= { hpnicfevtModuleRouterType 21 }
hpnicfevtModuleRt-Fxs4                        OBJECT IDENTIFIER ::= { hpnicfevtModuleRouterType 22 }
hpnicfevtModuleRt-Fxo4                        OBJECT IDENTIFIER ::= { hpnicfevtModuleRouterType 23 }
hpnicfevtModuleRt-Em4                         OBJECT IDENTIFIER ::= { hpnicfevtModuleRouterType 24 }
hpnicfevtModuleRt-Sab                         OBJECT IDENTIFIER ::= { hpnicfevtModuleRouterType 25 }
hpnicfevtModuleRt-E1vi                        OBJECT IDENTIFIER ::= { hpnicfevtModuleRouterType 26 }
hpnicfevtModuleRt-Am12                        OBJECT IDENTIFIER ::= { hpnicfevtModuleRouterType 27 }
hpnicfevtModuleRt-Am6                         OBJECT IDENTIFIER ::= { hpnicfevtModuleRouterType 28 }
hpnicfevtModuleRt-Ndec                        OBJECT IDENTIFIER ::= { hpnicfevtModuleRouterType 29 }
hpnicfevtModuleRt-Newsa2                      OBJECT IDENTIFIER ::= { hpnicfevtModuleRouterType 30 }
hpnicfevtModuleRt-Aux                         OBJECT IDENTIFIER ::= { hpnicfevtModuleRouterType 31 }
hpnicfevtModuleRt-Console                     OBJECT IDENTIFIER ::= { hpnicfevtModuleRouterType 32 }
hpnicfevtModuleRt-Sic-wan                     OBJECT IDENTIFIER ::= { hpnicfevtModuleRouterType 33 }
hpnicfevtModuleRt-Sic-1fe                     OBJECT IDENTIFIER ::= { hpnicfevtModuleRouterType 34 }
hpnicfevtModuleRt-Sic-1sa                     OBJECT IDENTIFIER ::= { hpnicfevtModuleRouterType 35 }
hpnicfevtModuleRt-Sic-3as                     OBJECT IDENTIFIER ::= { hpnicfevtModuleRouterType 36 }
hpnicfevtModuleRt-Sic-1e1                     OBJECT IDENTIFIER ::= { hpnicfevtModuleRouterType 37 }
hpnicfevtModuleRt-Sic-1t1                     OBJECT IDENTIFIER ::= { hpnicfevtModuleRouterType 38 }
hpnicfevtModuleRt-Sic-1bu                     OBJECT IDENTIFIER ::= { hpnicfevtModuleRouterType 39 }
hpnicfevtModuleRt-Sic-2bu                     OBJECT IDENTIFIER ::= { hpnicfevtModuleRouterType 40 }
hpnicfevtModuleRt-Sic-1bs                     OBJECT IDENTIFIER ::= { hpnicfevtModuleRouterType 41 }
hpnicfevtModuleRt-Sic-2bs                     OBJECT IDENTIFIER ::= { hpnicfevtModuleRouterType 42 }
hpnicfevtModuleRt-Sic-1am                     OBJECT IDENTIFIER ::= { hpnicfevtModuleRouterType 43 }
hpnicfevtModuleRt-Sic-2am                     OBJECT IDENTIFIER ::= { hpnicfevtModuleRouterType 44 }
hpnicfevtModuleRt-Sic-1em                     OBJECT IDENTIFIER ::= { hpnicfevtModuleRouterType 45 }
hpnicfevtModuleRt-Sic-2em                     OBJECT IDENTIFIER ::= { hpnicfevtModuleRouterType 46 }
hpnicfevtModuleRt-Sic-1fxs                    OBJECT IDENTIFIER ::= { hpnicfevtModuleRouterType 47 }
hpnicfevtModuleRt-Sic-2fxs                    OBJECT IDENTIFIER ::= { hpnicfevtModuleRouterType 48 }
hpnicfevtModuleRt-Sic-1fxo                    OBJECT IDENTIFIER ::= { hpnicfevtModuleRouterType 49 }
hpnicfevtModuleRt-Sic-2fxo                    OBJECT IDENTIFIER ::= { hpnicfevtModuleRouterType 50 }
hpnicfevtModuleRt-Fcm6                        OBJECT IDENTIFIER ::= { hpnicfevtModuleRouterType 51 }
hpnicfevtModuleRt-Sa8                         OBJECT IDENTIFIER ::= { hpnicfevtModuleRouterType 52 }
hpnicfevtModuleRt-T11                         OBJECT IDENTIFIER ::= { hpnicfevtModuleRouterType 53 }
hpnicfevtModuleRt-T12                         OBJECT IDENTIFIER ::= { hpnicfevtModuleRouterType 54 }
hpnicfevtModuleRt-T14                         OBJECT IDENTIFIER ::= { hpnicfevtModuleRouterType 55 }
hpnicfevtModuleRt-T1vi                        OBJECT IDENTIFIER ::= { hpnicfevtModuleRouterType 56 }
hpnicfevtModuleRt-Fcm4                        OBJECT IDENTIFIER ::= { hpnicfevtModuleRouterType 57 }
hpnicfevtModuleRt-Fcm2                        OBJECT IDENTIFIER ::= { hpnicfevtModuleRouterType 58 }
hpnicfevtModuleRt-Rtb21ce3                    OBJECT IDENTIFIER ::= { hpnicfevtModuleRouterType 59 }
hpnicfevtModuleRt-Ame6                        OBJECT IDENTIFIER ::= { hpnicfevtModuleRouterType 60 }
hpnicfevtModuleRt-Ame12                       OBJECT IDENTIFIER ::= { hpnicfevtModuleRouterType 61 }
hpnicfevtModuleRt-E11-f                       OBJECT IDENTIFIER ::= { hpnicfevtModuleRouterType 65 }
hpnicfevtModuleRt-E12-f                       OBJECT IDENTIFIER ::= { hpnicfevtModuleRouterType 66 }
hpnicfevtModuleRt-E14-f                       OBJECT IDENTIFIER ::= { hpnicfevtModuleRouterType 67 }
hpnicfevtModuleRt-T11-f                       OBJECT IDENTIFIER ::= { hpnicfevtModuleRouterType 68 }
hpnicfevtModuleRt-T12-f                       OBJECT IDENTIFIER ::= { hpnicfevtModuleRouterType 69 }
hpnicfevtModuleRt-T14-f                       OBJECT IDENTIFIER ::= { hpnicfevtModuleRouterType 70 }
hpnicfevtModuleRt-E11-f-17                    OBJECT IDENTIFIER ::= { hpnicfevtModuleRouterType 71 }
hpnicfevtModuleRt-T11-f-17                    OBJECT IDENTIFIER ::= { hpnicfevtModuleRouterType 72 }
hpnicfevtModuleRt-Rtb21ct3                    OBJECT IDENTIFIER ::= { hpnicfevtModuleRouterType 73 }
hpnicfevtModuleRt-Atmadsl1                    OBJECT IDENTIFIER ::= { hpnicfevtModuleRouterType 74 }
hpnicfevtModuleRt-Atmadsl2                    OBJECT IDENTIFIER ::= { hpnicfevtModuleRouterType 75 }
hpnicfevtModuleRt-Atm155m                     OBJECT IDENTIFIER ::= { hpnicfevtModuleRouterType 76 }
hpnicfevtModuleRt-Ase8                        OBJECT IDENTIFIER ::= { hpnicfevtModuleRouterType 77 }
hpnicfevtModuleRt-Ase16                       OBJECT IDENTIFIER ::= { hpnicfevtModuleRouterType 78 }
hpnicfevtModuleRt-Sae4                        OBJECT IDENTIFIER ::= { hpnicfevtModuleRouterType 79 }
hpnicfevtModuleRt-Sae2                        OBJECT IDENTIFIER ::= { hpnicfevtModuleRouterType 80 }
hpnicfevtModuleRt-Atmshdsl1                   OBJECT IDENTIFIER ::= { hpnicfevtModuleRouterType 90 }
hpnicfevtModuleRt-Atmshdsl2                   OBJECT IDENTIFIER ::= { hpnicfevtModuleRouterType 91 }
hpnicfevtModuleRt-Atmshdsl4                   OBJECT IDENTIFIER ::= { hpnicfevtModuleRouterType 92 }
hpnicfevtModuleRt-Atm25m                      OBJECT IDENTIFIER ::= { hpnicfevtModuleRouterType 93 }
hpnicfevtModuleRt-Atme3                       OBJECT IDENTIFIER ::= { hpnicfevtModuleRouterType 94 }
hpnicfevtModuleRt-Atmt3                       OBJECT IDENTIFIER ::= { hpnicfevtModuleRouterType 95 }
hpnicfevtModuleRt-Xdsl-fec                    OBJECT IDENTIFIER ::= { hpnicfevtModuleRouterType 96 }
hpnicfevtModuleRt-Xdsl-adsl                   OBJECT IDENTIFIER ::= { hpnicfevtModuleRouterType 97 }
hpnicfevtModuleRt-Xdsl-gshdsl                 OBJECT IDENTIFIER ::= { hpnicfevtModuleRouterType 98 }
hpnicfevtModuleRt-Xdsl-bri                    OBJECT IDENTIFIER ::= { hpnicfevtModuleRouterType 99 }
hpnicfevtModuleRt-Xdsl-scc                    OBJECT IDENTIFIER ::= { hpnicfevtModuleRouterType 100 }
hpnicfevtModuleRt-Ge1                         OBJECT IDENTIFIER ::= { hpnicfevtModuleRouterType 101 }
hpnicfevtModuleRt-Pos155m                     OBJECT IDENTIFIER ::= { hpnicfevtModuleRouterType 102 }
hpnicfevtModuleRt-Cpos                        OBJECT IDENTIFIER ::= { hpnicfevtModuleRouterType 103 }
hpnicfevtModuleRt-Fe1op                       OBJECT IDENTIFIER ::= { hpnicfevtModuleRouterType 104 }
hpnicfevtModuleRt-Sae8                        OBJECT IDENTIFIER ::= { hpnicfevtModuleRouterType 105 }
hpnicfevtModuleRt-Atm155m-mm                  OBJECT IDENTIFIER ::= { hpnicfevtModuleRouterType 106 }
hpnicfevtModuleRt-Atm155m-sm                  OBJECT IDENTIFIER ::= { hpnicfevtModuleRouterType 107 }
hpnicfevtModuleRt-Atm155m-sml                 OBJECT IDENTIFIER ::= { hpnicfevtModuleRouterType 108 }
hpnicfevtModuleRt-Fe1op-sfx                   OBJECT IDENTIFIER ::= { hpnicfevtModuleRouterType 109 }
hpnicfevtModuleRt-Fe1op-mfx                   OBJECT IDENTIFIER ::= { hpnicfevtModuleRouterType 110 }
hpnicfevtModuleRt-Cpos-t1                     OBJECT IDENTIFIER ::= { hpnicfevtModuleRouterType 111 }
hpnicfevtModuleRt-Ge1op                       OBJECT IDENTIFIER ::= { hpnicfevtModuleRouterType 112 }
hpnicfevtModuleRt-Ge2op                       OBJECT IDENTIFIER ::= { hpnicfevtModuleRouterType 113 }
hpnicfevtModuleRt-Ge2                         OBJECT IDENTIFIER ::= { hpnicfevtModuleRouterType 114 }
hpnicfevtModuleRt-Fix-1wan                    OBJECT IDENTIFIER ::= { hpnicfevtModuleRouterType 115 }
hpnicfevtModuleRt-Fix-1sae                    OBJECT IDENTIFIER ::= { hpnicfevtModuleRouterType 116 }
hpnicfevtModuleRt-Cavium                      OBJECT IDENTIFIER ::= { hpnicfevtModuleRouterType 117 }
hpnicfevtModuleRt-Sic1Eth                     OBJECT IDENTIFIER ::= { hpnicfevtModuleRouterType 118 }
hpnicfevtModuleRt-atm1ADSLI                   OBJECT IDENTIFIER ::= { hpnicfevtModuleRouterType 119 }
hpnicfevtModuleRt-atm2ADSLI                   OBJECT IDENTIFIER ::= { hpnicfevtModuleRouterType 120 }
hpnicfevtModuleRt-fix-e11                     OBJECT IDENTIFIER ::= { hpnicfevtModuleRouterType 121 }
hpnicfevtModuleRt-fix-t11                     OBJECT IDENTIFIER ::= { hpnicfevtModuleRouterType 122 }
hpnicfevtModuleRt-e18-75                      OBJECT IDENTIFIER ::= { hpnicfevtModuleRouterType 123 }
hpnicfevtModuleRt-e18-120                     OBJECT IDENTIFIER ::= { hpnicfevtModuleRouterType 124 }
hpnicfevtModuleRt-t18                         OBJECT IDENTIFIER ::= { hpnicfevtModuleRouterType 125 }
hpnicfevtModuleRt-sic-1vifxs                  OBJECT IDENTIFIER ::= { hpnicfevtModuleRouterType 126 }
hpnicfevtModuleRt-sic-1vifxo                  OBJECT IDENTIFIER ::= { hpnicfevtModuleRouterType 127 }
hpnicfevtModuleRt-sic-2vifxs                  OBJECT IDENTIFIER ::= { hpnicfevtModuleRouterType 128 }
hpnicfevtModuleRt-sic-2vifxo                  OBJECT IDENTIFIER ::= { hpnicfevtModuleRouterType 129 }
hpnicfevtModuleRt-xdsl-fec-new                OBJECT IDENTIFIER ::= { hpnicfevtModuleRouterType 130 }
hpnicfevtModuleRt-xdsl-sa                     OBJECT IDENTIFIER ::= { hpnicfevtModuleRouterType 131 }
hpnicfevtModuleRt-bs4                         OBJECT IDENTIFIER ::= { hpnicfevtModuleRouterType 132 }
hpnicfevtModuleRt-ima-8e175                   OBJECT IDENTIFIER ::= { hpnicfevtModuleRouterType 133 }
hpnicfevtModuleRt-ima-8e1120                  OBJECT IDENTIFIER ::= { hpnicfevtModuleRouterType 134 }
hpnicfevtModuleRt-ima-4e175                   OBJECT IDENTIFIER ::= { hpnicfevtModuleRouterType 135 }
hpnicfevtModuleRt-ima-4e1120                  OBJECT IDENTIFIER ::= { hpnicfevtModuleRouterType 136 }
hpnicfevtModuleRt-ima-8t1                     OBJECT IDENTIFIER ::= { hpnicfevtModuleRouterType 137 }
hpnicfevtModuleRt-ima-4t1                     OBJECT IDENTIFIER ::= { hpnicfevtModuleRouterType 138 }
hpnicfevtModuleRt-sic-1t1f                    OBJECT IDENTIFIER ::= { hpnicfevtModuleRouterType 139 }
hpnicfevtModuleRt-sic-1e1f                    OBJECT IDENTIFIER ::= { hpnicfevtModuleRouterType 140 }
hpnicfevtModuleRt-VG-16fxs                    OBJECT IDENTIFIER ::= { hpnicfevtModuleRouterType 141 }
hpnicfevtModuleRt-VG-32fxs                    OBJECT IDENTIFIER ::= { hpnicfevtModuleRouterType 142 }
hpnicfevtModuleRt-VG-8fxo                     OBJECT IDENTIFIER ::= { hpnicfevtModuleRouterType 143 }
hpnicfevtModuleRt-VG-2fe                      OBJECT IDENTIFIER ::= { hpnicfevtModuleRouterType 144 }
hpnicfevtModuleRt-sib                         OBJECT IDENTIFIER ::= { hpnicfevtModuleRouterType 145 } -- SIB card
hpnicfevtModuleRt-cie32                       OBJECT IDENTIFIER ::= { hpnicfevtModuleRouterType 146 } -- 32M SSRAM CIE card
hpnicfevtModuleRt-cie64                       OBJECT IDENTIFIER ::= { hpnicfevtModuleRouterType 147 } -- 64M SSRAM CIE card
hpnicfevtModuleRt-cie96                       OBJECT IDENTIFIER ::= { hpnicfevtModuleRouterType 148 } -- 96M SSRAM CIE card
hpnicfevtModuleRt-Fe4                         OBJECT IDENTIFIER ::= { hpnicfevtModuleRouterType 149 } -- 4FE card
hpnicfevtModuleRt-fxs4fxo1                    OBJECT IDENTIFIER ::= { hpnicfevtModuleRouterType 150 } -- 4 Port Foreign Exchange Station and 1 Port Foreign Exchange Office Interface
hpnicfevtModuleRt-atm1shdsl4wire              OBJECT IDENTIFIER ::= { hpnicfevtModuleRouterType 151 } -- G.SHDSL 4 wire MIM card, 1 port
hpnicfevtModuleRt-atmIma4shdsl                OBJECT IDENTIFIER ::= { hpnicfevtModuleRouterType 152 } -- G.SHDSL 8 wire MIM card, 4 ports
hpnicfevtModuleRt-ls4                         OBJECT IDENTIFIER ::= { hpnicfevtModuleRouterType 153 } -- 4 Ports Layer 2 Lanswitch Module
hpnicfevtModuleRt-ls8                         OBJECT IDENTIFIER ::= { hpnicfevtModuleRouterType 154 } -- 8 Ports Layer 2 Lanswitch Module
hpnicfevtModuleRt-ls16                        OBJECT IDENTIFIER ::= { hpnicfevtModuleRouterType 155 } -- 16 Ports Layer 2 Lanswitch Module
hpnicfevtModuleRt-sic-adls2plus-isdn          OBJECT IDENTIFIER ::= { hpnicfevtModuleRouterType 156 } -- ADLS2Plus SIC card, ISDN port
hpnicfevtModuleRt-sic-adls2plus-pots          OBJECT IDENTIFIER ::= { hpnicfevtModuleRouterType 157 } -- ADLS2Plus SIC card, POTS port
hpnicfevtModuleRt-ft3                         OBJECT IDENTIFIER ::= { hpnicfevtModuleRouterType 158 } -- 1 Port Fractional T3 module
hpnicfevtModuleRt-ce32                        OBJECT IDENTIFIER ::= { hpnicfevtModuleRouterType 159 } -- 2 Port Channelized E3 module
hpnicfevtModuleRt-bsv2                        OBJECT IDENTIFIER ::= { hpnicfevtModuleRouterType 160 } -- 2 Port BSV module
hpnicfevtModuleRt-bsv4                        OBJECT IDENTIFIER ::= { hpnicfevtModuleRouterType 161 } -- 4 Port BSV module
hpnicfevtModuleRt-RPU                         OBJECT IDENTIFIER ::= { hpnicfevtModuleRouterType 162 } -- Route processing unit
hpnicfevtModuleRt-ERPU                        OBJECT IDENTIFIER ::= { hpnicfevtModuleRouterType 163 } -- Enhanced route processing unit
hpnicfevtModuleRt-SSL                         OBJECT IDENTIFIER ::= { hpnicfevtModuleRouterType 164 } -- SSL Encrypt Card
hpnicfevtModuleRt-NSA                         OBJECT IDENTIFIER ::= { hpnicfevtModuleRouterType 165 } -- NSA Encrypt Card

--
-- 166 to 199 reserved for other devices
--


--
-- 200 to 399 reserved for normal routers part I
--
hpnicfevtModuleRT-SIC-1GEC                    OBJECT IDENTIFIER ::= { hpnicfevtModuleRouterType 200 } -- 1-Port 10M/100M/1000M COMBO Ethernet Interface SIC Module
hpnicfevtModuleRT-24FSW                       OBJECT IDENTIFIER ::= { hpnicfevtModuleRouterType 201 } -- 24-Port 10M/100M and 2-Port 1000BASE-T/1000BASE-X(COMBO) Ethernet L2 Switch Module
hpnicfevtModuleRT-24FSWP                      OBJECT IDENTIFIER ::= { hpnicfevtModuleRouterType 202 } -- 24-Port 10M/100M(WITH POE) and 2-Port 1000BASE-T/1000BASE-X(COMBO) Ethernet L2 Switch Module
hpnicfevtModuleRT-16FSW                       OBJECT IDENTIFIER ::= { hpnicfevtModuleRouterType 203 } -- 16-Port 10M/100M Ethernet L2 Switch Module
hpnicfevtModuleRT-16FSWP                      OBJECT IDENTIFIER ::= { hpnicfevtModuleRouterType 204 } -- 16-Port 10M/100M(WITH POE) Ethernet L2 Switch Module
hpnicfevtModuleRT-1VE1                        OBJECT IDENTIFIER ::= { hpnicfevtModuleRouterType 205 } -- 1-Port Voice E1 Module
hpnicfevtModuleRT-1VT1                        OBJECT IDENTIFIER ::= { hpnicfevtModuleRouterType 206 } -- 1-Port Voice T1 Module
hpnicfevtModuleRT-2VE1                        OBJECT IDENTIFIER ::= { hpnicfevtModuleRouterType 207 } -- 2-Port Voice E1 Module
hpnicfevtModuleRT-2VT1                        OBJECT IDENTIFIER ::= { hpnicfevtModuleRouterType 208 } -- 2-Port Voice T1 Module
hpnicfevtModuleRT-SIC-4FSW                    OBJECT IDENTIFIER ::= { hpnicfevtModuleRouterType 209 } -- 4-Port 10M/100M Ethernet L2 Switch Module (RJ45)
hpnicfevtModuleRT-SIC-4FSWP                   OBJECT IDENTIFIER ::= { hpnicfevtModuleRouterType 210 } -- 4-Port 10M/100M Ethernet L2 Switch Module(RJ45,WITH POE)
hpnicfevtModuleRT-DSIC-9FSW                   OBJECT IDENTIFIER ::= { hpnicfevtModuleRouterType 211 } -- 9-Port 10M/100M Ethernet L2 Switch Module(RJ45)
hpnicfevtModuleRT-DSIC-9FSWP                  OBJECT IDENTIFIER ::= { hpnicfevtModuleRouterType 212 } -- 9-Port 10M/100M Ethernet L2 Switch Module(RJ45,WITH POE)
hpnicfevtModuleRT-SIC-1VE1                    OBJECT IDENTIFIER ::= { hpnicfevtModuleRouterType 213 } -- 1-Port Voice E1 SIC Interface Module
hpnicfevtModuleRT-SIC-1VT1                    OBJECT IDENTIFIER ::= { hpnicfevtModuleRouterType 214 } -- 1-Port Voice T1 SIC Interface Module
hpnicfevtModuleRT-VCPM                        OBJECT IDENTIFIER ::= { hpnicfevtModuleRouterType 215 } -- Voice Co-Processing Module
hpnicfevtModuleRT-VPM                         OBJECT IDENTIFIER ::= { hpnicfevtModuleRouterType 216 } -- 32-Channels Voice Processing Module
hpnicfevtModuleRT-VPMA                        OBJECT IDENTIFIER ::= { hpnicfevtModuleRouterType 217 } -- 16-Channels Voice Processing Module
hpnicfevtModuleRT-VPMB                        OBJECT IDENTIFIER ::= { hpnicfevtModuleRouterType 218 } -- 8-Channels Voice Processing Module
hpnicfevtModuleRT-VPMC                        OBJECT IDENTIFIER ::= { hpnicfevtModuleRouterType 219 } -- 24-Channels Voice Processing Module
hpnicfevtModuleRt-fe18-75                     OBJECT IDENTIFIER ::= { hpnicfevtModuleRouterType 220 } -- 8 Port FE1(75 O) module
hpnicfevtModuleRt-fe18-120                    OBJECT IDENTIFIER ::= { hpnicfevtModuleRouterType 221 } -- 8 Port FE1(120 O) module
hpnicfevtModuleRt-ft18                        OBJECT IDENTIFIER ::= { hpnicfevtModuleRouterType 222 } -- 8 Port FT1 module
hpnicfevtModuleRt-CF                          OBJECT IDENTIFIER ::= { hpnicfevtModuleRouterType 223 } -- Compact Flash Card
hpnicfevtModuleRt-bsv2-v2                     OBJECT IDENTIFIER ::= { hpnicfevtModuleRouterType 224 } -- 2 Port BSV Version 2
hpnicfevtModuleRt-e1vi1-v2                    OBJECT IDENTIFIER ::= { hpnicfevtModuleRouterType 225 } -- E1VI Version 2
hpnicfevtModuleRt-e1vi2                       OBJECT IDENTIFIER ::= { hpnicfevtModuleRouterType 226 } -- 2 Port E1VI
hpnicfevtModuleRt-t1vi1-v2                    OBJECT IDENTIFIER ::= { hpnicfevtModuleRouterType 227 } -- T1VI Version 2
hpnicfevtModuleRt-t1vi2                       OBJECT IDENTIFIER ::= { hpnicfevtModuleRouterType 228 } -- 2 Port T1VI
hpnicfevtModuleRt-osm                         OBJECT IDENTIFIER ::= { hpnicfevtModuleRouterType 229 } -- Open Service Module
hpnicfevtModuleRt-sd707                       OBJECT IDENTIFIER ::= { hpnicfevtModuleRouterType 230 } -- Encryption Accelerator
hpnicfevtModuleRt-dm-epri                     OBJECT IDENTIFIER ::= { hpnicfevtModuleRouterType 231 } -- E1 Pri Digital Modem
hpnicfevtModuleRt-dm-tpri                     OBJECT IDENTIFIER ::= { hpnicfevtModuleRouterType 232 } -- T1 Pri Digital Modem
hpnicfevtModuleRt-ERPU-H                      OBJECT IDENTIFIER ::= { hpnicfevtModuleRouterType 233 } -- Enhanced route processing unit with only one optic GE interface
hpnicfevtModuleRT-SIC-1BSV                    OBJECT IDENTIFIER ::= { hpnicfevtModuleRouterType 234 } -- 1-Port Bri S/T VoiceInterface SIC Module
hpnicfevtModuleRT-SIC-2BSV                    OBJECT IDENTIFIER ::= { hpnicfevtModuleRouterType 235 } -- 2-Port Bri S/T VoiceInterface SIC Module
hpnicfevtModuleRt-gbe8                        OBJECT IDENTIFIER ::= { hpnicfevtModuleRouterType 236 } -- 8-Port Gigabit Ethernet interface card
hpnicfevtModuleRt-gbe4                        OBJECT IDENTIFIER ::= { hpnicfevtModuleRouterType 237 } -- 4-Port Gigabit Ethernet interface card
hpnicfevtModuleRt-cpos2-v2                    OBJECT IDENTIFIER ::= { hpnicfevtModuleRouterType 238 } -- 2-Port Channelized Low speed POS interface card
hpnicfevtModuleRt-cpos1-v2                    OBJECT IDENTIFIER ::= { hpnicfevtModuleRouterType 239 } -- 1-Port Channelized Low speed POS interface card
hpnicfevtModuleRt-oap                         OBJECT IDENTIFIER ::= { hpnicfevtModuleRouterType 240 } -- Open Application Platform
hpnicfevtModuleRT-48FSWP                      OBJECT IDENTIFIER ::= { hpnicfevtModuleRouterType 241 } -- 46-Port 10M/100M(With PoE) and 2-Port 1000BASE-T(With PoE) Ethernet L2 Switch Module
hpnicfevtModuleRT-48FSW                       OBJECT IDENTIFIER ::= { hpnicfevtModuleRouterType 242 } -- 46-Port 10M/100M and 2-Port 1000BASE-T Ethernet L2 Switch Module
hpnicfevtModuleRT-ASM                         OBJECT IDENTIFIER ::= { hpnicfevtModuleRouterType 243 } -- Anti-virus Security Module
hpnicfevtModuleRT-SIC-1FEF                    OBJECT IDENTIFIER ::= { hpnicfevtModuleRouterType 244 } -- 1-Port 100M SFP Interface SIC Module
hpnicfevtModuleRT-XMIM-24FSW                  OBJECT IDENTIFIER ::= { hpnicfevtModuleRouterType 245 } -- 24-Port 10M/100MBASE-TX Ethernet L2 Switch Interface XMIM-Module
hpnicfevtModuleRT-WLAN-AG-1RADIO              OBJECT IDENTIFIER ::= { hpnicfevtModuleRouterType 246 } -- Mini PCI Interface 802.11ag Radio Frequency Adapter Card
hpnicfevtModuleRT-1CE3                        OBJECT IDENTIFIER ::= { hpnicfevtModuleRouterType 247 } -- 1-port E3/CE3/FE3 Compatible Interface Module,(M)
hpnicfevtModuleRT-XMIM-16FSW                  OBJECT IDENTIFIER ::= { hpnicfevtModuleRouterType 248 } -- 16-Port 10M/100MBASE-TX Ethernet L2 Switch Interface XMIM-Module
hpnicfevtModuleRT-OAPS                        OBJECT IDENTIFIER ::= { hpnicfevtModuleRouterType 249 } -- Open Application System-Smart
hpnicfevtModuleRT-NAM                         OBJECT IDENTIFIER ::= { hpnicfevtModuleRouterType 250 } -- Network Analysis Module
hpnicfevtModuleRT-RPE-X1                      OBJECT IDENTIFIER ::= { hpnicfevtModuleRouterType 251 } -- Route Processing Engine
hpnicfevtModuleRT-FIP-100                     OBJECT IDENTIFIER ::= { hpnicfevtModuleRouterType 252 } -- Flexible Interface Platform-100
hpnicfevtModuleRT-FIP-200                     OBJECT IDENTIFIER ::= { hpnicfevtModuleRouterType 253 } -- Flexible Interface Platform-200
hpnicfevtModuleRT-SIC-8AS                     OBJECT IDENTIFIER ::= { hpnicfevtModuleRouterType 254 } -- 8-Port Asynchronous Serial
hpnicfevtModuleRT-WAAM                        OBJECT IDENTIFIER ::= { hpnicfevtModuleRouterType 255 } -- WAN Application Acceleration Module
hpnicfevtModuleRt-msp4p-OC3c                  OBJECT IDENTIFIER ::= { hpnicfevtModuleRouterType 256 } -- 4 Port Multi-Speed POS Interface Module (OC-3c Mode)
hpnicfevtModuleRt-1pos-oc48                   OBJECT IDENTIFIER ::= { hpnicfevtModuleRouterType 257 } -- 1 Port Super-Speed POS Interface Card
hpnicfevtModuleRt-xgbe                        OBJECT IDENTIFIER ::= { hpnicfevtModuleRouterType 258 } -- 1-Port 10GBASE-R/W Ethernet Optical Interface Card
hpnicfevtModuleRT-EADM                        OBJECT IDENTIFIER ::= { hpnicfevtModuleRouterType 259 } -- EAD Integrated Module
hpnicfevtModuleRT-VCM                         OBJECT IDENTIFIER ::= { hpnicfevtModuleRouterType 260 } -- Voice Convergence Module
hpnicfevtModuleRT-SIC-2FXS1FXO                OBJECT IDENTIFIER ::= { hpnicfevtModuleRouterType 261 } -- 2FXS+1FXO Interface SIC-Module
hpnicfevtModuleRT-8FXS8FXO                    OBJECT IDENTIFIER ::= { hpnicfevtModuleRouterType 262 } -- 8FXS+8FXO Interface Module
hpnicfevtModuleRT-16FXS                       OBJECT IDENTIFIER ::= { hpnicfevtModuleRouterType 263 } -- 16-port FXS Interface Module
hpnicfevtModuleRT-OAPS-ICM                    OBJECT IDENTIFIER ::= { hpnicfevtModuleRouterType 264 } -- OAPS Information Communication Module
hpnicfevtModuleRT-OAP-ICM                     OBJECT IDENTIFIER ::= { hpnicfevtModuleRouterType 265 } -- OAP Information Communication Module
hpnicfevtModuleRT-8fe                         OBJECT IDENTIFIER ::= { hpnicfevtModuleRouterType 266 } -- 8-Port 100M Ethernet Electrical Interface Module
hpnicfevtModuleRT-4gbp                        OBJECT IDENTIFIER ::= { hpnicfevtModuleRouterType 267 } -- 4-Port GigaBit Ethernet Optical Interface Module(SFP)
hpnicfevtModuleRT-MPU-G2                      OBJECT IDENTIFIER ::= { hpnicfevtModuleRouterType 268 } -- Main Processor Unit
hpnicfevtModuleRT-OAPS-OCE                    OBJECT IDENTIFIER ::= { hpnicfevtModuleRouterType 269 } -- OAPS Office Communication Engine
hpnicfevtModuleRT-OAP-OCE                     OBJECT IDENTIFIER ::= { hpnicfevtModuleRouterType 270 } -- OAP Office Communication Engine
hpnicfevtModuleRT-OAPS-ICE                    OBJECT IDENTIFIER ::= { hpnicfevtModuleRouterType 271 } -- OAPS Information Communication Engine
hpnicfevtModuleRT-OAP-ICE                     OBJECT IDENTIFIER ::= { hpnicfevtModuleRouterType 272 } -- OAP Information Communication Module
hpnicfevtModuleRT-SIC-16AS                    OBJECT IDENTIFIER ::= { hpnicfevtModuleRouterType 273 } -- 16-Port Asynchronous Serial
hpnicfevtModuleRT-SPE-FWM                     OBJECT IDENTIFIER ::= { hpnicfevtModuleRouterType 274 } -- Gigabit Firewall Module
hpnicfevtModuleRT-cls2p                       OBJECT IDENTIFIER ::= { hpnicfevtModuleRouterType 275 } -- 2 Port Channelized 155M POS to E3/T3 Interface Module
hpnicfevtModuleRT-cls1p                       OBJECT IDENTIFIER ::= { hpnicfevtModuleRouterType 276 } -- 1 Port Channelized 155M POS to E3/T3 Interface Module
hpnicfevtModuleRT-SIC-2E1-F                   OBJECT IDENTIFIER ::= { hpnicfevtModuleRouterType 277 } -- 2-Port Fractional E1 Interface SIC-Module
hpnicfevtModuleRT-SIC-1E1-F-V2                OBJECT IDENTIFIER ::= { hpnicfevtModuleRouterType 278 } -- 1-Port Fractional E1 Interface SIC-Module
hpnicfevtModuleRT-MCU                         OBJECT IDENTIFIER ::= { hpnicfevtModuleRouterType 279 } -- Main Control Unit
hpnicfevtModuleRT-ACU                         OBJECT IDENTIFIER ::= { hpnicfevtModuleRouterType 280 } -- Access Control Unit
hpnicfevtModuleRT-1ATM-OC3                    OBJECT IDENTIFIER ::= { hpnicfevtModuleRouterType 281 } -- 1-Port Asynchronous Transfer Mode OC3 Board
hpnicfevtModuleRT-RSE-X1                      OBJECT IDENTIFIER ::= { hpnicfevtModuleRouterType 282 } -- Main Processing Unit With XAUI Switch
hpnicfevtModuleRT-FIP-210                     OBJECT IDENTIFIER ::= { hpnicfevtModuleRouterType 283 } -- Multi-core CPU Line Processing Board with 2 Combo GE Ports
hpnicfevtModuleRT-1expa                       OBJECT IDENTIFIER ::= { hpnicfevtModuleRouterType 284 } -- 1 Port Ten Gigabit Interface Module
hpnicfevtModuleRT-WLAN-SIC-N-1RADIO           OBJECT IDENTIFIER ::= { hpnicfevtModuleRouterType 285 } -- 1 wlan-radio 802.11n sic Interface Board
hpnicfevtModuleRT-WLAN-SIC-BG-1RADIO          OBJECT IDENTIFIER ::= { hpnicfevtModuleRouterType 286 } -- 1 wlan-radio 802.11b/g sic Interface Board
hpnicfevtModuleRT-al2p                        OBJECT IDENTIFIER ::= { hpnicfevtModuleRouterType 287 } -- 2 Port 155M ATM Interface Module
hpnicfevtModuleRT-msp2p-OC3c                  OBJECT IDENTIFIER ::= { hpnicfevtModuleRouterType 288 } -- 2-Port Multi-speed POS Interface Module (OC-3c Mode)
hpnicfevtModuleRT-8gbp                        OBJECT IDENTIFIER ::= { hpnicfevtModuleRouterType 289 } -- 8-Port GigaBit Ethernet Optical Interface Module(SFP)
hpnicfevtModuleRT-SIC-EPON                    OBJECT IDENTIFIER ::= { hpnicfevtModuleRouterType 290 } -- 1-Port Ethernet Passive Optical Network SIC Card(SFF)
hpnicfevtModuleRT-SIC-3G-GSM-H3               OBJECT IDENTIFIER ::= { hpnicfevtModuleRouterType 291 } -- 3G Wireless WAN Interface SIC Module Supporting GPRS/EDGE/UMTS/HSDPA
hpnicfevtModuleRT-msp2p-OC12c                 OBJECT IDENTIFIER ::= { hpnicfevtModuleRouterType 292 } -- 2-Port Multi-speed POS Interface Module (OC-12c Mode)
hpnicfevtModuleRt-msp4p-OC12c                 OBJECT IDENTIFIER ::= { hpnicfevtModuleRouterType 293 } -- 4-Port Multi-Speed POS Interface Module (OC-12c Mode)
hpnicfevtModuleRt-al1p                        OBJECT IDENTIFIER ::= { hpnicfevtModuleRouterType 294 } -- 1-Port 155M ATM Interface Module
hpnicfevtModuleRt-OAP-100                     OBJECT IDENTIFIER ::= { hpnicfevtModuleRouterType 295 } -- Open Application Platform Module
hpnicfevtModuleRt-FIP-110                     OBJECT IDENTIFIER ::= { hpnicfevtModuleRouterType 296 } -- Flexible Interface Platform-110
hpnicfevtModuleRt-OSM-SSM                     OBJECT IDENTIFIER ::= { hpnicfevtModuleRouterType 297 } -- OSM Security Services Module
hpnicfevtModuleRt-OAP-SSM                     OBJECT IDENTIFIER ::= { hpnicfevtModuleRouterType 298 } -- OAP Security Services Module
hpnicfevtModuleRt-rs2p                        OBJECT IDENTIFIER ::= { hpnicfevtModuleRouterType 299 } -- 2-Port OC-48c/STM-16c RPR Interface Module
hpnicfevtModuleRt-SAP-48GBE                   OBJECT IDENTIFIER ::= { hpnicfevtModuleRouterType 300 } -- 48-Port 1000Base-T Gigabit Ethernet Interface Module
hpnicfevtModuleRt-SAP-48GBP                   OBJECT IDENTIFIER ::= { hpnicfevtModuleRouterType 301 } -- 48-Port 1000BASE Ethernet Optical Interface Module
hpnicfevtModuleRt-SAP-24GBP                   OBJECT IDENTIFIER ::= { hpnicfevtModuleRouterType 302 } -- 24-Port 1000BASE Ethernet Optical Interface Module
hpnicfevtModuleRt-SPE-SSL                     OBJECT IDENTIFIER ::= { hpnicfevtModuleRouterType 303 } -- SSL VPN Module
hpnicfevtModuleRt-SIC-AUDIO                   OBJECT IDENTIFIER ::= { hpnicfevtModuleRouterType 304 } -- MOH and PAGE Interface SIC Module Supporting MOH/PAGE/DOOR RELAY
hpnicfevtModuleRt-FIC-1E1POS-H3               OBJECT IDENTIFIER ::= { hpnicfevtModuleRouterType 305 } -- 1-Port E1 POS Interface FIC Module
hpnicfevtModuleRt-DSIC-4FXS1FXO               OBJECT IDENTIFIER ::= { hpnicfevtModuleRouterType 306 } -- 4FXS+1FXO Interface DSIC-Module
hpnicfevtModuleRt-FIC-CPOS                    OBJECT IDENTIFIER ::= { hpnicfevtModuleRouterType 307 } -- 1-Port CPOS Interface Module
hpnicfevtModuleRt-DSIC-1SHDSL-8W              OBJECT IDENTIFIER ::= { hpnicfevtModuleRouterType 308 } -- 1-Port 8 Wire SHDSL Interface DSIC Module
hpnicfevtModuleRt-SIC-3G-TD                   OBJECT IDENTIFIER ::= { hpnicfevtModuleRouterType 309 } -- 1 Port TD-Cellular Interface SIC-Module
hpnicfevtModuleRt-SIC-3G-CDMA                 OBJECT IDENTIFIER ::= { hpnicfevtModuleRouterType 310 } -- 1 Port CDMA-Cellular Interface SIC-Module
hpnicfevtModuleRt-SIC-3G-HSPA                 OBJECT IDENTIFIER ::= { hpnicfevtModuleRouterType 311 } -- 1 Port HSPA-Cellular Interface SIC-Module
hpnicfevtModuleRt-FIC-OAP-V2                  OBJECT IDENTIFIER ::= { hpnicfevtModuleRouterType 312 } -- Open Application Platform V2 FIC Module
hpnicfevtModuleRt-MIM-OAP-V2                  OBJECT IDENTIFIER ::= { hpnicfevtModuleRouterType 313 } -- Open Application Platform V2 MIM Module
hpnicfevtModuleRt-MIM-OAPS-V2                 OBJECT IDENTIFIER ::= { hpnicfevtModuleRouterType 314 } -- Open Application System-Smart V2 MIM Module
hpnicfevtModuleRt-HMIM-1CT3                   OBJECT IDENTIFIER ::= { hpnicfevtModuleRouterType 315 } -- 1 Port Channelized T3 Interface HMIM Module
hpnicfevtModuleRt-HMIM-1CE3                   OBJECT IDENTIFIER ::= { hpnicfevtModuleRouterType 316 } -- 1 Port Channelized E3 Interface HMIM Module
hpnicfevtModuleRt-HMIM-1POS                   OBJECT IDENTIFIER ::= { hpnicfevtModuleRouterType 317 } -- 1 Port POS Interface HMIM Module
hpnicfevtModuleRt-HMIM-2SAE                   OBJECT IDENTIFIER ::= { hpnicfevtModuleRouterType 318 } -- 2 Port SAE Interface HMIM Module
hpnicfevtModuleRt-HMIM-4SAE                   OBJECT IDENTIFIER ::= { hpnicfevtModuleRouterType 319 } -- 4 Port SAE Interface HMIM Module
hpnicfevtModuleRt-HMIM-8SAE                   OBJECT IDENTIFIER ::= { hpnicfevtModuleRouterType 320 } -- 8 Port SAE Interface HMIM Module
hpnicfevtModuleRt-HMIM-8ASE                   OBJECT IDENTIFIER ::= { hpnicfevtModuleRouterType 321 } -- 8 Port ASE Interface HMIM Module
hpnicfevtModuleRt-HMIM-16ASE                  OBJECT IDENTIFIER ::= { hpnicfevtModuleRouterType 322 } -- 16 Port ASE Interface HMIM Module
hpnicfevtModuleRt-HMIM-1E1                    OBJECT IDENTIFIER ::= { hpnicfevtModuleRouterType 323 } -- 1 Port E1 Interface HMIM Module
hpnicfevtModuleRt-HMIM-2E1                    OBJECT IDENTIFIER ::= { hpnicfevtModuleRouterType 324 } -- 2 Port E1 Interface HMIM Module
hpnicfevtModuleRt-HMIM-4E1                    OBJECT IDENTIFIER ::= { hpnicfevtModuleRouterType 325 } -- 4 Port E1 Interface HMIM Module
hpnicfevtModuleRt-HMIM-8E1-75                 OBJECT IDENTIFIER ::= { hpnicfevtModuleRouterType 326 } -- 8 Port E1(75 o) Interface HMIM Module
hpnicfevtModuleRt-HMIM-1E1-F                  OBJECT IDENTIFIER ::= { hpnicfevtModuleRouterType 327 } -- 1 Port E1-F Interface HMIM Module
hpnicfevtModuleRt-HMIM-2E1-F                  OBJECT IDENTIFIER ::= { hpnicfevtModuleRouterType 328 } -- 2 Port E1-F Interface HMIM Module
hpnicfevtModuleRt-HMIM-4E1-F                  OBJECT IDENTIFIER ::= { hpnicfevtModuleRouterType 329 } -- 4 Port E1-F Interface HMIM Module
hpnicfevtModuleRt-HMIM-8E1-F-75               OBJECT IDENTIFIER ::= { hpnicfevtModuleRouterType 330 } -- 8 Port E1-F(75 o) Interface HMIM Module
hpnicfevtModuleRt-HMIM-6AM                    OBJECT IDENTIFIER ::= { hpnicfevtModuleRouterType 331 } -- 6 Port AM Interface HMIM Module
hpnicfevtModuleRt-HMIM-6FCM                   OBJECT IDENTIFIER ::= { hpnicfevtModuleRouterType 332 } -- 6 Port FCM Interface HMIM Module
hpnicfevtModuleRt-HMIM-2T1                    OBJECT IDENTIFIER ::= { hpnicfevtModuleRouterType 333 } -- 2 Port T1 Interface HMIM Module
hpnicfevtModuleRt-HMIM-4T1-F                  OBJECT IDENTIFIER ::= { hpnicfevtModuleRouterType 334 } -- 4 Port T1-F Interface HMIM Module
hpnicfevtModuleRt-HMIM-8T1                    OBJECT IDENTIFIER ::= { hpnicfevtModuleRouterType 335 } -- 8 Port T1 Interface HMIM Module
hpnicfevtModuleRt-HMIM-8T1-F                  OBJECT IDENTIFIER ::= { hpnicfevtModuleRouterType 336 } -- 8 Port T1-F Interface HMIM Module
hpnicfevtModuleRt-HMIM-1VE1                   OBJECT IDENTIFIER ::= { hpnicfevtModuleRouterType 337 } -- 1 Port Voice E1 Interface HMIM Module
hpnicfevtModuleRt-HMIM-1VT1                   OBJECT IDENTIFIER ::= { hpnicfevtModuleRouterType 338 } -- 1 Port Voice T1 Interface HMIM Module
hpnicfevtModuleRt-HMIM-2VE1                   OBJECT IDENTIFIER ::= { hpnicfevtModuleRouterType 339 } -- 2 Port Voice E1 Interface HMIM Module
hpnicfevtModuleRt-HMIM-2VT1                   OBJECT IDENTIFIER ::= { hpnicfevtModuleRouterType 340 } -- 2 Port Voice T1 Interface HMIM Module
hpnicfevtModuleRt-HMIM-8FXS8FXO               OBJECT IDENTIFIER ::= { hpnicfevtModuleRouterType 341 } -- 8FXS + 8FXO Interface HMIM Module
hpnicfevtModuleRt-HMIM-16FXS                  OBJECT IDENTIFIER ::= { hpnicfevtModuleRouterType 342 } -- 16 Port FXS Interface HMIM Module
hpnicfevtModuleRt-HMIM-4FXS                   OBJECT IDENTIFIER ::= { hpnicfevtModuleRouterType 343 } -- 4 Port FXS Interface HMIM Module
hpnicfevtModuleRt-HMIM-4FXO                   OBJECT IDENTIFIER ::= { hpnicfevtModuleRouterType 344 } -- 4 Port FXO Interface HMIM Module
hpnicfevtModuleRt-HMIM-4EM                    OBJECT IDENTIFIER ::= { hpnicfevtModuleRouterType 345 } -- 4 Port E&M Interface HMIM Module
hpnicfevtModuleRt-HMIM-4BSV                   OBJECT IDENTIFIER ::= { hpnicfevtModuleRouterType 346 } -- 4 Port Bri S/T Voice Interface HMIM Module
hpnicfevtModuleRt-SIC-CNDE                    OBJECT IDENTIFIER ::= { hpnicfevtModuleRouterType 347 } -- CNDE Crypto Engine SIC-Module
hpnicfevtModuleRt-ESM-CNDE                    OBJECT IDENTIFIER ::= { hpnicfevtModuleRouterType 348 } -- CNDE Crypto Engine ESM-Module
hpnicfevtModuleRt-ESM-CNDE-M                  OBJECT IDENTIFIER ::= { hpnicfevtModuleRouterType 349 } -- CNDE Crypto Engine MiniPCI-ESM-Module
hpnicfevtModuleRt-SR6602-X1                   OBJECT IDENTIFIER ::= { hpnicfevtModuleRouterType 350 } -- 2U Router Host(4GE Combo/2 HIM slot)
hpnicfevtModuleRt-SR6602-X2                   OBJECT IDENTIFIER ::= { hpnicfevtModuleRouterType 351 } -- 2U Router Host(4GE Combo/2 10G SFP+/2 HIM slot)
hpnicfevtModuleRt-MCP-X1                      OBJECT IDENTIFIER ::= { hpnicfevtModuleRouterType 352 } -- Main Controller and Processor X1
hpnicfevtModuleRt-MCP-X2                      OBJECT IDENTIFIER ::= { hpnicfevtModuleRouterType 353 } -- Main Controller and Processor X2
hpnicfevtModuleRt-FIP-10                      OBJECT IDENTIFIER ::= { hpnicfevtModuleRouterType 354 } -- Flexible Interface Platform 10
hpnicfevtModuleRt-FIP-20                      OBJECT IDENTIFIER ::= { hpnicfevtModuleRouterType 355 } -- Flexible Interface Platform 20
hpnicfevtModuleRt-RSE-X2                      OBJECT IDENTIFIER ::= { hpnicfevtModuleRouterType 356 } -- Route Switch Engine X2
hpnicfevtModuleRt-FIP-600                     OBJECT IDENTIFIER ::= { hpnicfevtModuleRouterType 357 } -- Flexible Interface Platform 600
hpnicfevtModuleRt-SAP-4EXP                    OBJECT IDENTIFIER ::= { hpnicfevtModuleRouterType 358 } -- 4-Port 10GBASE-R/W Ethernet Optical Interface Module(SFP+)
hpnicfevtModuleRt-SFE-X1                      OBJECT IDENTIFIER ::= { hpnicfevtModuleRouterType 359 } -- Switch Fabric Engine X1
hpnicfevtModuleRt-SFE-A1                      OBJECT IDENTIFIER ::= { hpnicfevtModuleRouterType 360 } -- Switch Fabric Engine A1
hpnicfevtModuleRt-HMIM-24GSW                  OBJECT IDENTIFIER ::= { hpnicfevtModuleRouterType 361 } -- 24-Port 10M/100M/1000MBASE-T Ethernet L2 Switch Interface HMIM_Module
hpnicfevtModuleRt-HMIM-24GSWP                 OBJECT IDENTIFIER ::= { hpnicfevtModuleRouterType 362 } -- 24-Port 10M/100M/1000MBASE-T(WITH POE) Ethernet L2 Switch Interface HMIM_Module
hpnicfevtModuleRt-MPU100                      OBJECT IDENTIFIER ::= { hpnicfevtModuleRouterType 363 } -- Main Processing Unit 100
hpnicfevtModuleRt-SPU100                      OBJECT IDENTIFIER ::= { hpnicfevtModuleRouterType 364 } -- Service Processing Unit 100
hpnicfevtModuleRt-SPU200                      OBJECT IDENTIFIER ::= { hpnicfevtModuleRouterType 365 } -- Service Processing Unit 200
hpnicfevtModuleRt-WLAN-N-1RADIO               OBJECT IDENTIFIER ::= { hpnicfevtModuleRouterType 366 } -- Mini PCI Interface 802.11n Radio Frequency Adapter Card
hpnicfevtModuleRt-3G-CDMA                     OBJECT IDENTIFIER ::= { hpnicfevtModuleRouterType 367 } -- 1 Port CDMA-Cellular Interface Adapter Card
hpnicfevtModuleRt-3G-WCDMA                    OBJECT IDENTIFIER ::= { hpnicfevtModuleRouterType 368 } -- 1 Port WCDMA-Cellular Interface Adapter Card
hpnicfevtModuleRt-3G-HSPAPLUS                 OBJECT IDENTIFIER ::= { hpnicfevtModuleRouterType 369 } -- 1 Port HSPA+-Cellular Interface Adapter Card
hpnicfevtModuleRt-VPM-128                     OBJECT IDENTIFIER ::= { hpnicfevtModuleRouterType 370 } -- 128-VoiceChannel VPM Module
hpnicfevtModuleRt-VPM-256                     OBJECT IDENTIFIER ::= { hpnicfevtModuleRouterType 371 } -- 256-VoiceChannel VPM Module
hpnicfevtModuleRt-VPM-512                     OBJECT IDENTIFIER ::= { hpnicfevtModuleRouterType 372 } -- 512-VoiceChannel VPM Module
hpnicfevtModuleRt-HMIM-8GEE                   OBJECT IDENTIFIER ::= { hpnicfevtModuleRouterType 373 } -- 8-port copper GigabitEthernet HMIM Module
hpnicfevtModuleRt-HMIM-4GEE                   OBJECT IDENTIFIER ::= { hpnicfevtModuleRouterType 374 } -- 4-port copper GigabitEthernet HMIM Module
hpnicfevtModuleRt-HMIM-2GEE                   OBJECT IDENTIFIER ::= { hpnicfevtModuleRouterType 375 } -- 2-port copper GigabitEthernet HMIM Module
hpnicfevtModuleRt-HMIM-8GEF                   OBJECT IDENTIFIER ::= { hpnicfevtModuleRouterType 376 } -- 8-port fiber GigabitEthernet HMIM Module
hpnicfevtModuleRt-HMIM-4GEF                   OBJECT IDENTIFIER ::= { hpnicfevtModuleRouterType 377 } -- 4-port fiber GigabitEthernet HMIM Module
hpnicfevtModuleRt-HMIM-2GEF                   OBJECT IDENTIFIER ::= { hpnicfevtModuleRouterType 378 } -- 2-port fiber GigabitEthernet HMIM Module
hpnicfevtModuleRt-SPU300                      OBJECT IDENTIFIER ::= { hpnicfevtModuleRouterType 379 } -- Service Processing Unit 300
hpnicfevtModuleRt-HMIM-1CPOS                  OBJECT IDENTIFIER ::= { hpnicfevtModuleRouterType 380 } -- 1-port CPOS Interface HMIM Module
hpnicfevtModuleRt-HMIM-2CPOS                  OBJECT IDENTIFIER ::= { hpnicfevtModuleRouterType 381 } -- 2-port CPOS Interface HMIM Module
hpnicfevtModuleRt-SPU100-5080                 OBJECT IDENTIFIER ::= { hpnicfevtModuleRouterType 382 } -- Service Processing Unit 100
hpnicfevtModuleRt-SPU200-5080                 OBJECT IDENTIFIER ::= { hpnicfevtModuleRouterType 383 } -- Service Processing Unit 200
hpnicfevtModuleRt-SPU300-5080                 OBJECT IDENTIFIER ::= { hpnicfevtModuleRouterType 384 } -- Service Processing Unit 300
hpnicfevtModuleRt-4G-LTE-Verizon              OBJECT IDENTIFIER ::= { hpnicfevtModuleRouterType 385 } -- 1 Port 4G-LTE-Verizon-Cellular Interface Adapter Card
hpnicfevtModuleRt-4G-LTE-Global               OBJECT IDENTIFIER ::= { hpnicfevtModuleRouterType 386 } -- 1 Port 4G-LTE-Global-Cellular Interface Adapter Card
hpnicfevtModuleRt-HMIM-1ATM-OC3               OBJECT IDENTIFIER ::= { hpnicfevtModuleRouterType 387 } -- 1-Port OC3 ATM MM/SM/SML HMIM Module
hpnicfevtModuleRt-SIC-1E1-V2                  OBJECT IDENTIFIER ::= { hpnicfevtModuleRouterType 388 } -- 1-Port E1/CE1/PRI Interface SIC Module
hpnicfevtModuleRt-FIP-300                     OBJECT IDENTIFIER ::= { hpnicfevtModuleRouterType 389 } -- Flexible Interface Platform 300
hpnicfevtModuleRt-FIP-310                     OBJECT IDENTIFIER ::= { hpnicfevtModuleRouterType 390 } -- Flexible Interface Platform 310
hpnicfevtModuleRt-TS8P                        OBJECT IDENTIFIER ::= { hpnicfevtModuleRouterType 391 } -- 8-Port OC-3c/OC-12c POS or Gigabit Ethernet Optical Interface Module(SFP)
hpnicfevtModuleRt-4G4P                        OBJECT IDENTIFIER ::= { hpnicfevtModuleRouterType 392 } -- 4-Port Gigabit Ethernet Optical Interface and 4-Port OC-3c POS Interface Module(SFP)
hpnicfevtModuleRt-SIC-4G-LTE-V                OBJECT IDENTIFIER ::= { hpnicfevtModuleRouterType 393 } -- 1 Port 4G-LTE-Verizon-Cellular Interface SIC-Module
hpnicfevtModuleRt-SIC-4G-LTE-A                OBJECT IDENTIFIER ::= { hpnicfevtModuleRouterType 394 } -- 1 Port 4G-LTE-AT&T-Cellular Interface SIC-Module
hpnicfevtModuleRt-SIC-4G-LTE-G                OBJECT IDENTIFIER ::= { hpnicfevtModuleRouterType 395 } -- 1 Port 4G-LTE-Global-Cellular Interface SIC-Module
hpnicfevtModuleRt-SIC-2SAE                    OBJECT IDENTIFIER ::= { hpnicfevtModuleRouterType 396 } -- 2 Port SAE Interface SIC Module
hpnicfevtModuleRt-SIC-4SAE                    OBJECT IDENTIFIER ::= { hpnicfevtModuleRouterType 397 } -- 4 Port SAE Interface SIC Module
hpnicfevtModuleRt-HMIM-OAP                    OBJECT IDENTIFIER ::= { hpnicfevtModuleRouterType 398 } -- Open Application Platform HMIM Interface Module with Cloud Virtualization Kernel
hpnicfevtModuleRt-HMIM-8GSW                   OBJECT IDENTIFIER ::= { hpnicfevtModuleRouterType 399 } -- 8-Port 10M/100M/1000MBASE-T Ethernet L2 Switch Interface HMIM-Module,including 2 Combo Ports

--
-- 400 to 599 reserved for security routers
--
hpnicfevtModuleRt-IPU                         OBJECT IDENTIFIER ::= { hpnicfevtModuleRouterType 400 } -- IPS Processing Unit
hpnicfevtModuleRt-MIM2GEBE-PCIE               OBJECT IDENTIFIER ::= { hpnicfevtModuleRouterType 401 } -- 2-port UTM GigabitEthernet Interface Module
hpnicfevtModuleRt-HIM12GE-PCIE                OBJECT IDENTIFIER ::= { hpnicfevtModuleRouterType 402 } -- 12-port GigabitEthernet Interface Module
hpnicfevtModuleRt-HIM2XGE-PCIE                OBJECT IDENTIFIER ::= { hpnicfevtModuleRouterType 403 } -- 2-port Ten-GigabitEthernet Interface Module
hpnicfevtModuleRt-IPU-T1000-M                 OBJECT IDENTIFIER ::= { hpnicfevtModuleRouterType 404 } -- IPS Processing Unit for T1000-M Mainboard Module
hpnicfevtModuleRt-IPU-GX4C                    OBJECT IDENTIFIER ::= { hpnicfevtModuleRouterType 405 } -- 4 Port Gigabit Fiber Module
hpnicfevtModuleRt-IPU-GT4C                    OBJECT IDENTIFIER ::= { hpnicfevtModuleRouterType 406 } -- 4 Port 1000BASE-T Module
hpnicfevtModuleRt-RPU-IAG2000-A               OBJECT IDENTIFIER ::= { hpnicfevtModuleRouterType 407 } -- Intelligence Application Gateway Module
hpnicfevtModuleRt-RPU-AFD1000-A               OBJECT IDENTIFIER ::= { hpnicfevtModuleRouterType 408 } -- Anomaly Flow Detector Module
hpnicfevtModuleRt-RPU-F5000-A                 OBJECT IDENTIFIER ::= { hpnicfevtModuleRouterType 409 } -- Advanced Firewall Module
hpnicfevtModuleRt-ACG-8800S3-MPU              OBJECT IDENTIFIER ::= { hpnicfevtModuleRouterType 410 } -- Main Control Unit,with 24 1000BASE-X/100BASE-FX Optical Ports,including 8 Combo Ports,SFP Req
hpnicfevtModuleRt-T5000S3-MPU                 OBJECT IDENTIFIER ::= { hpnicfevtModuleRouterType 411 } -- Main Control Unit,with 24 1000BASE-X/100BASE-FX Optical Ports,including 8 Combo Ports,SFP Req
hpnicfevtModuleRt-NS21S2MSPB0                 OBJECT IDENTIFIER ::= { hpnicfevtModuleRouterType 412 } -- Multi Service Processing Module
hpnicfevtModuleRt-NS11S2MSPB0                 OBJECT IDENTIFIER ::= { hpnicfevtModuleRouterType 413 } -- Multi Service Processing Module
hpnicfevtModuleRt-NSQ1WLAN                    OBJECT IDENTIFIER ::= { hpnicfevtModuleRouterType 414 } -- Dual-Band,Multi-Mode 802.11a/b/g Wireless LAN card
hpnicfevtModuleRt-NSQ1GP4U0                   OBJECT IDENTIFIER ::= { hpnicfevtModuleRouterType 415 } -- 4 Port Gigabit Fiber Module
hpnicfevtModuleRt-NSQ1GP8C40                  OBJECT IDENTIFIER ::= { hpnicfevtModuleRouterType 416 } -- 12-Port GigabitEthernet Interface Module,with 4 Combo Ports,8 Fiber Ports
hpnicfevtModuleRt-NSQ1XS2U0                   OBJECT IDENTIFIER ::= { hpnicfevtModuleRouterType 417 } -- 2-Port Ten GigabitEthernet Interface Module
hpnicfevtModuleRt-NSQ1G24XS60                 OBJECT IDENTIFIER ::= { hpnicfevtModuleRouterType 418 } -- 12-copper 12-fiber and 6-XGE Interface Module
hpnicfevtModuleRt-NSQ1TGX4EA0                 OBJECT IDENTIFIER ::= { hpnicfevtModuleRouterType 419 } -- 4-XGE Fabric Interface Module
hpnicfevtModuleRt-NSQ1FAB08D0                 OBJECT IDENTIFIER ::= { hpnicfevtModuleRouterType 420 } -- Switch Module
hpnicfevtModuleRt-NSQ1TGS32SF0                OBJECT IDENTIFIER ::= { hpnicfevtModuleRouterType 421 } -- 32-XGE Fabric Interface Module
hpnicfevtModuleRt-NSQ1QGS4SF0                 OBJECT IDENTIFIER ::= { hpnicfevtModuleRouterType 422 } -- 4-XGE Fabric Interface Module
hpnicfevtModuleRt-NSQ1GP24TXEA0               OBJECT IDENTIFIER ::= { hpnicfevtModuleRouterType 423 } -- 16-GE Fabric,8-GE Combo,2-XGE Interface Module
hpnicfevtModuleRt-NSQ1GP48EB0                 OBJECT IDENTIFIER ::= { hpnicfevtModuleRouterType 424 } -- 48-GE Fabric Interface Module
hpnicfevtModuleRt-NSQ1FWCEA0                  OBJECT IDENTIFIER ::= { hpnicfevtModuleRouterType 425 } -- Firewall Module
hpnicfevtModuleRt-NSQ1GT48EA0                 OBJECT IDENTIFIER ::= { hpnicfevtModuleRouterType 426 } -- 48-GE Copper Interface
hpnicfevtModuleRt-NSQ1TGS8EA0                 OBJECT IDENTIFIER ::= { hpnicfevtModuleRouterType 427 } -- 8-XGE Fabric Interface
hpnicfevtModuleRt-NSQ1FAB04B0                 OBJECT IDENTIFIER ::= { hpnicfevtModuleRouterType 428 } -- Switch Module
hpnicfevtModuleRt-NSQ1FAB12D0                 OBJECT IDENTIFIER ::= { hpnicfevtModuleRouterType 429 } -- Switch Module
hpnicfevtModuleRt-NSQ1SUPB0                   OBJECT IDENTIFIER ::= { hpnicfevtModuleRouterType 430 } -- Main Control Module
hpnicfevtModuleRt-VFW1000                     OBJECT IDENTIFIER ::= { hpnicfevtModuleRouterType 431 } -- Virtual Firwall Gateway module
hpnicfevtModuleRt-NSQ1CGC2SE0                 OBJECT IDENTIFIER ::= { hpnicfevtModuleRouterType 432 } -- 2 Port 100GBASE Ethernet Optical Interface Board(CFP)(SE)
hpnicfevtModuleRt-VLB1000                     OBJECT IDENTIFIER ::= { hpnicfevtModuleRouterType 433 } -- Virtual LB module


--
-- 600 to 799 reserved for voice routers
--
hpnicfevtModuleRt-VG-8fxs                     OBJECT IDENTIFIER ::= { hpnicfevtModuleRouterType 600 } -- 8 Port Foreign Exchange Station module
hpnicfevtModuleRt-VG-24fxs                    OBJECT IDENTIFIER ::= { hpnicfevtModuleRouterType 601 } -- 24 Port Foreign Exchange Station module
hpnicfevtModuleRt-VG-24fxs24fxo               OBJECT IDENTIFIER ::= { hpnicfevtModuleRouterType 602 } -- 24 Port Foreign Exchange Station and 24 Port Foreign Exchange Office module
hpnicfevtModuleRt-VG-MPU                      OBJECT IDENTIFIER ::= { hpnicfevtModuleRouterType 603 } -- Media Processing Unit
hpnicfevtModuleRt-MIM-VCX-CONNECT-P-3C        OBJECT IDENTIFIER ::= { hpnicfevtModuleRouterType 604 } -- MIM VCX Connect Primary module
hpnicfevtModuleRt-MIM-VCX-CONNECT-S-3C        OBJECT IDENTIFIER ::= { hpnicfevtModuleRouterType 605 } -- MIM VCX Connect Secondary module
hpnicfevtModuleRt-MIM-VCX-3C                  OBJECT IDENTIFIER ::= { hpnicfevtModuleRouterType 606 } -- MIM VCX Enterprise module
hpnicfevtModuleRt-VNIC-VMXNET3                OBJECT IDENTIFIER ::= { hpnicfevtModuleRouterType 607 } -- 1 Port Gigabit Ethernet interface virtual VMXNET3 module
hpnicfevtModuleRt-VNIC-E1000                  OBJECT IDENTIFIER ::= { hpnicfevtModuleRouterType 608 } -- 1 Port Gigabit Ethernet interface virtual E1000 module
hpnicfevtModuleRt-VNIC-VIRTIO                 OBJECT IDENTIFIER ::= { hpnicfevtModuleRouterType 609 } -- 1 Port Gigabit Ethernet interface virtual VIRTIO module
hpnicfevtModuleRt-VNIC-RTL8139                OBJECT IDENTIFIER ::= { hpnicfevtModuleRouterType 610 } -- 1 Port Gigabit Ethernet interface virtual RTL8139 module
hpnicfevtModuleRt-VNIC-IXGBEVF                OBJECT IDENTIFIER ::= { hpnicfevtModuleRouterType 611 } -- 1 Port Ten-Gigabit Ethernet interface virtual IXGBEVF module


--
-- 800 to 999 reserved for normal routers part II
--
hpnicfevtModuleRt-SIC-4GSW                    OBJECT IDENTIFIER ::= { hpnicfevtModuleRouterType 800 } -- 4-Port 10M/100M/1000MBASE-T Ethernet L2 Switch Interface SIC-Module
hpnicfevtModuleRt-SIC-4GSWP                   OBJECT IDENTIFIER ::= { hpnicfevtModuleRouterType 801 } -- 4-Port 10M/100M/1000MBASE-T(WITH POE) Ethernet L2 Switch Interface SIC-Module
hpnicfevtModuleRt-SIC-1GEC-V2                 OBJECT IDENTIFIER ::= { hpnicfevtModuleRouterType 802 } -- 1-Port Combo Gigabit Ethernet Interface SIC-Module
hpnicfevtModuleRt-4G-LTE-ATT                  OBJECT IDENTIFIER ::= { hpnicfevtModuleRouterType 803 } -- 1 Port 4G-LTE-ATT-Cellular Interface Adapter Card
hpnicfevtModuleRt-4G-TD-LTE                   OBJECT IDENTIFIER ::= { hpnicfevtModuleRouterType 804 } -- 1 Port 4G-TD-LTE-Cellular Interface Adapter Card
hpnicfevtModuleRt-FIP-240                     OBJECT IDENTIFIER ::= { hpnicfevtModuleRouterType 805 } -- Flexible Interface Platform 240
hpnicfevtModuleRt-8GBP-V2                     OBJECT IDENTIFIER ::= { hpnicfevtModuleRouterType 806 } -- 8-Port GigaBit Ethernet Optical Interface Module(SFP) V2
hpnicfevtModuleRt-HMIM-CNDE                   OBJECT IDENTIFIER ::= { hpnicfevtModuleRouterType 807 } -- CNDE Crypto Engine HMIM-Module
hpnicfevtModuleRt-4G-LTE-Mobile               OBJECT IDENTIFIER ::= { hpnicfevtModuleRouterType 808 } -- 1 Port 4G-LTE-Mobile-Cellular Interface Adapter Card
hpnicfevtModuleRt-SIC-4G-LTE-M                OBJECT IDENTIFIER ::= { hpnicfevtModuleRouterType 809 } -- 1 Port 4G-LTE/TD-SCDMA/WCDMA Cellular Interface SIC-Module
hpnicfevtModuleRt-CRSE-X3                     OBJECT IDENTIFIER ::= { hpnicfevtModuleRouterType 810 } -- Carrier Route Switch Engine X3
hpnicfevtModuleRt-CFIP-300                    OBJECT IDENTIFIER ::= { hpnicfevtModuleRouterType 811 } -- Carrier Flexible Interface Platform 300
hpnicfevtModuleRt-CFIP-310                    OBJECT IDENTIFIER ::= { hpnicfevtModuleRouterType 812 } -- Carrier Flexible Interface Platform 310
hpnicfevtModuleRt-CSAP-4EXP                   OBJECT IDENTIFIER ::= { hpnicfevtModuleRouterType 813 } -- Carrier 4-Port 10GBASE-R/W Ethernet Optical Interface Module(SFP+)
hpnicfevtModuleRt-RSU                         OBJECT IDENTIFIER ::= { hpnicfevtModuleRouterType 814 } -- Route Switch Unit
hpnicfevtModuleRt-CFIP-610                    OBJECT IDENTIFIER ::= { hpnicfevtModuleRouterType 815 } -- Carrier Flexible Interface Platform 610
hpnicfevtModuleRt-2EXP                        OBJECT IDENTIFIER ::= { hpnicfevtModuleRouterType 816 } -- 2-Port 10GBASE-R/W Ethernet Optical Interface Module(SFP+)
hpnicfevtModuleRt-16GBP                       OBJECT IDENTIFIER ::= { hpnicfevtModuleRouterType 817 } -- 16-Port Gigabit Ethernet Optical Interface Module(SFP)
hpnicfevtModuleRt-CFIP-240                    OBJECT IDENTIFIER ::= { hpnicfevtModuleRouterType 818 } -- Carrier Flexible Interface Platform 240
hpnicfevtModuleRt-RSE-X3                      OBJECT IDENTIFIER ::= { hpnicfevtModuleRouterType 819 } -- Route Switch Engine X3
hpnicfevtModuleRt-SAP-8EXP                    OBJECT IDENTIFIER ::= { hpnicfevtModuleRouterType 820 } -- 8-Port 10GBASE-R/W Ethernet Optical Interface Module(SFP+)
hpnicfevtModuleRt-SAP-16EXP                   OBJECT IDENTIFIER ::= { hpnicfevtModuleRouterType 821 } -- 16-Port 10GBASE-R/W Ethernet Optical Interface Module(SFP+)
hpnicfevtModuleRt-PU1P                        OBJECT IDENTIFIER ::= { hpnicfevtModuleRouterType 822 } -- 1-Port 10G POS/RPR Interface Module(XFP)
hpnicfevtModuleRt-RSU100                      OBJECT IDENTIFIER ::= { hpnicfevtModuleRouterType 823 } -- Router Switch Unit 100
hpnicfevtModuleRt-SAP-2QGP                    OBJECT IDENTIFIER ::= { hpnicfevtModuleRouterType 824 } -- 2-Port 40GBASE Ethernet Optical Interface Module(QSFP+)
hpnicfevtModuleRt-CSFE-X1                     OBJECT IDENTIFIER ::= { hpnicfevtModuleRouterType 825 } -- Carrier Switch Fabric Engine X1


--
-- reserved for other brands from 5000
--
hpevtModuleRt-SIC-EPRI                     OBJECT IDENTIFIER ::= { hpnicfevtModuleRouterType 5000 } -- 1-Port E1/CE1/PRI Interface Card
hpevtModuleRt-MIM-1E1-V2                   OBJECT IDENTIFIER ::= { hpnicfevtModuleRouterType 5001 } -- 1-Port CE1/PRI Interface Module
hpevtModuleRt-MIM-1E1-F-V2                 OBJECT IDENTIFIER ::= { hpnicfevtModuleRouterType 5002 } -- 1-Port E1 & Fractional E1 Interface Module
hpevtModuleRt-MIM-2E1-F-V2                 OBJECT IDENTIFIER ::= { hpnicfevtModuleRouterType 5003 } -- 2-Port E1 & Fractional E1 Interface Module
hpevtModuleRt-MIM-4E1-F-V2                 OBJECT IDENTIFIER ::= { hpnicfevtModuleRouterType 5004 } -- 4-Port E1 & Fractional E1 Interface Module
hpevtModuleRt-MIM-8E1-75                   OBJECT IDENTIFIER ::= { hpnicfevtModuleRouterType 5005 } -- 8-port E1/CE1/PRI Module(75ohm)
hpevtModuleRt-MIM-8E1-75-F                 OBJECT IDENTIFIER ::= { hpnicfevtModuleRouterType 5006 } -- 8-Port E1 Module-Fractional(75ohm)
hpevtModuleRt-MIM-8T1                      OBJECT IDENTIFIER ::= { hpnicfevtModuleRouterType 5007 } -- 8-Port T1 Interface Module
hpevtModuleRt-MIM-8T1-F                    OBJECT IDENTIFIER ::= { hpnicfevtModuleRouterType 5008 } -- 8-Port T1 Module-Fractional
hpevtModuleRt-MIM-IMA-8E1-75               OBJECT IDENTIFIER ::= { hpnicfevtModuleRouterType 5009 } -- 8-Port E1 ATM IMA Interface Module(75ohm)
hpevtModuleRt-FIC-2E1-V3                   OBJECT IDENTIFIER ::= { hpnicfevtModuleRouterType 5010 } -- 2-Port E1/CE1/PRI Interface FIC Module
hpevtModuleRt-FIC-IMA-8T1-V2               OBJECT IDENTIFIER ::= { hpnicfevtModuleRouterType 5011 } -- 8-Port T1 ATM IMA Interface FIC Module


-- hpnicfevtModuleSwitchType cards are slot-cards specific to the Switch.
hpnicfevtModuleSwitchType  OBJECT IDENTIFIER ::= { hpnicfevtModule 4 }

--hpnicfevtModuleNULL(0),
hpnicfevtModuleSw-10OR100M                    OBJECT IDENTIFIER ::= { hpnicfevtModuleSwitchType 1 }
hpnicfevtModuleSw-1000BASE-LX-SM              OBJECT IDENTIFIER ::= { hpnicfevtModuleSwitchType 2 }
hpnicfevtModuleSw-1000BASE-SX-MM              OBJECT IDENTIFIER ::= { hpnicfevtModuleSwitchType 3 }
hpnicfevtModuleSw-1000BASE-TX                 OBJECT IDENTIFIER ::= { hpnicfevtModuleSwitchType 4 }
hpnicfevtModuleSw-100M-SINGLEMODE-FX          OBJECT IDENTIFIER ::= { hpnicfevtModuleSwitchType 5 }
hpnicfevtModuleSw-100M-MULTIMODE-FX           OBJECT IDENTIFIER ::= { hpnicfevtModuleSwitchType 6 }
hpnicfevtModuleSw-100M-100BASE-TX             OBJECT IDENTIFIER ::= { hpnicfevtModuleSwitchType 7 }
hpnicfevtModuleSw-100M-HUB                    OBJECT IDENTIFIER ::= { hpnicfevtModuleSwitchType 8 }
hpnicfevtModuleSw-VDSL                        OBJECT IDENTIFIER ::= { hpnicfevtModuleSwitchType 9 }
hpnicfevtModuleSw-STACK                       OBJECT IDENTIFIER ::= { hpnicfevtModuleSwitchType 10 }
hpnicfevtModuleSw-1000BASE-ZENITH-FX          OBJECT IDENTIFIER ::= { hpnicfevtModuleSwitchType 11 }
hpnicfevtModuleSw-1000BASE-LONG-FX            OBJECT IDENTIFIER ::= { hpnicfevtModuleSwitchType 12 }
hpnicfevtModuleSw-ADSL                        OBJECT IDENTIFIER ::= { hpnicfevtModuleSwitchType 13 }
hpnicfevtModuleSw-4T10OR100-4FX100SM          OBJECT IDENTIFIER ::= { hpnicfevtModuleSwitchType 14 }
hpnicfevtModuleSw-4T10OR100-4FX100MM          OBJECT IDENTIFIER ::= { hpnicfevtModuleSwitchType 15 }
hpnicfevtModuleSw-VSPL                        OBJECT IDENTIFIER ::= { hpnicfevtModuleSwitchType 16 }
hpnicfevtModuleSw-ASPL                        OBJECT IDENTIFIER ::= { hpnicfevtModuleSwitchType 17 }
hpnicfevtModuleSw-1000M-SFP                   OBJECT IDENTIFIER ::= { hpnicfevtModuleSwitchType 18 }
hpnicfevtModuleSw-LS82O2CM                    OBJECT IDENTIFIER ::= { hpnicfevtModuleSwitchType 19 }
hpnicfevtModuleSw-LS82P2CM                    OBJECT IDENTIFIER ::= { hpnicfevtModuleSwitchType 20 }
hpnicfevtModuleSw-LS82O4GM                    OBJECT IDENTIFIER ::= { hpnicfevtModuleSwitchType 21 }
hpnicfevtModuleSw-LS82GB4C                    OBJECT IDENTIFIER ::= { hpnicfevtModuleSwitchType 22 }
hpnicfevtModuleSw-LS82GT4C                    OBJECT IDENTIFIER ::= { hpnicfevtModuleSwitchType 23 }
hpnicfevtModuleSw-LS82ST4C                    OBJECT IDENTIFIER ::= { hpnicfevtModuleSwitchType 24 }
hpnicfevtModuleSw-BOARD-LS82DSPU              OBJECT IDENTIFIER ::= { hpnicfevtModuleSwitchType 25 }
hpnicfevtModuleSw-BOARD-LS81GP8U              OBJECT IDENTIFIER ::= { hpnicfevtModuleSwitchType 26 }
hpnicfevtModuleSw-BOARD-LS82GT20              OBJECT IDENTIFIER ::= { hpnicfevtModuleSwitchType 27 }
hpnicfevtModuleSw-BOARD-LS82FE48              OBJECT IDENTIFIER ::= { hpnicfevtModuleSwitchType 28 }
hpnicfevtModuleSw-LS82T24B                    OBJECT IDENTIFIER ::= { hpnicfevtModuleSwitchType 29 }
hpnicfevtModuleSw-LSB1SRPA                    OBJECT IDENTIFIER ::= { hpnicfevtModuleSwitchType 30 }
hpnicfevtModuleSw-LSB1FT48A                   OBJECT IDENTIFIER ::= { hpnicfevtModuleSwitchType 31 }
hpnicfevtModuleSw-LSB1FT48B                   OBJECT IDENTIFIER ::= { hpnicfevtModuleSwitchType 32 }
hpnicfevtModuleSw-LSB1F48GA                   OBJECT IDENTIFIER ::= { hpnicfevtModuleSwitchType 33 }
hpnicfevtModuleSw-LSB1F48GB                   OBJECT IDENTIFIER ::= { hpnicfevtModuleSwitchType 34 }
hpnicfevtModuleSw-LSB1FP20A                   OBJECT IDENTIFIER ::= { hpnicfevtModuleSwitchType 35 }
hpnicfevtModuleSw-LSB1FP20B                   OBJECT IDENTIFIER ::= { hpnicfevtModuleSwitchType 36 }
hpnicfevtModuleSw-FT48A                       OBJECT IDENTIFIER ::= { hpnicfevtModuleSwitchType 37 }
hpnicfevtModuleSw-GP4U                        OBJECT IDENTIFIER ::= { hpnicfevtModuleSwitchType 38 }
hpnicfevtModuleSw-GP2U                        OBJECT IDENTIFIER ::= { hpnicfevtModuleSwitchType 39 }
hpnicfevtModuleSw-TGX1A                       OBJECT IDENTIFIER ::= { hpnicfevtModuleSwitchType 40 }
hpnicfevtModuleSw-1000BASE-LX-SM-IR-SC        OBJECT IDENTIFIER ::= { hpnicfevtModuleSwitchType 41 }
hpnicfevtModuleSw-1000BASE-SX-MM-SR-SC        OBJECT IDENTIFIER ::= { hpnicfevtModuleSwitchType 42 }
hpnicfevtModuleSw-1000BASE-T-RJ45             OBJECT IDENTIFIER ::= { hpnicfevtModuleSwitchType 43 }
hpnicfevtModuleSw-100BASE-FX-SM-IR-SC         OBJECT IDENTIFIER ::= { hpnicfevtModuleSwitchType 44 }
hpnicfevtModuleSw-100BASE-FX-MM-SR-SC         OBJECT IDENTIFIER ::= { hpnicfevtModuleSwitchType 45 }
hpnicfevtModuleSw-GIGA-STACK-1M-PC            OBJECT IDENTIFIER ::= { hpnicfevtModuleSwitchType 46 }
hpnicfevtModuleSw-1000BASE-LX-SM-VLR-LC       OBJECT IDENTIFIER ::= { hpnicfevtModuleSwitchType 47 }
hpnicfevtModuleSw-1000BASE-LX-SM-LR-LC        OBJECT IDENTIFIER ::= { hpnicfevtModuleSwitchType 48 }
hpnicfevtModuleSw-100BASE-FX-SM-LR-SC         OBJECT IDENTIFIER ::= { hpnicfevtModuleSwitchType 49 }
hpnicfevtModuleSw-1000BASE-X-GBIC             OBJECT IDENTIFIER ::= { hpnicfevtModuleSwitchType 50 }
hpnicfevtModuleSw-100M-SINGLEMODE-FX-LC       OBJECT IDENTIFIER ::= { hpnicfevtModuleSwitchType 51 }
hpnicfevtModuleSw-100M-MULTIMODE-FX-LC        OBJECT IDENTIFIER ::= { hpnicfevtModuleSwitchType 52 }
hpnicfevtModuleSw-1000BASE-4SFP               OBJECT IDENTIFIER ::= { hpnicfevtModuleSwitchType 53 }
hpnicfevtModuleSw-1000BASE-4GBIC              OBJECT IDENTIFIER ::= { hpnicfevtModuleSwitchType 54 }
hpnicfevtModuleSw-1000BASE-FIXED-4SFP         OBJECT IDENTIFIER ::= { hpnicfevtModuleSwitchType 55 }
hpnicfevtModuleSw-1000BASE-FIXED-4GBIC        OBJECT IDENTIFIER ::= { hpnicfevtModuleSwitchType 56 }
hpnicfevtModuleSw-LSB1GP12A                   OBJECT IDENTIFIER ::= { hpnicfevtModuleSwitchType 57 }
hpnicfevtModuleSw-LSB1GP12B                   OBJECT IDENTIFIER ::= { hpnicfevtModuleSwitchType 58 }
hpnicfevtModuleSw-LSB1TGX1A                   OBJECT IDENTIFIER ::= { hpnicfevtModuleSwitchType 59 }
hpnicfevtModuleSw-LSB1TGX1B                   OBJECT IDENTIFIER ::= { hpnicfevtModuleSwitchType 60 }
hpnicfevtModuleSw-LSB1P4G8A                   OBJECT IDENTIFIER ::= { hpnicfevtModuleSwitchType 61 }
hpnicfevtModuleSw-LSB1P4G8B                   OBJECT IDENTIFIER ::= { hpnicfevtModuleSwitchType 62 }
hpnicfevtModuleSw-LSB1A4G8A                   OBJECT IDENTIFIER ::= { hpnicfevtModuleSwitchType 63 }
hpnicfevtModuleSw-LSB1A4G8B                   OBJECT IDENTIFIER ::= { hpnicfevtModuleSwitchType 64 }
hpnicfevtModuleSw-FT48C                       OBJECT IDENTIFIER ::= { hpnicfevtModuleSwitchType 65 }
hpnicfevtModuleSw-FP20                        OBJECT IDENTIFIER ::= { hpnicfevtModuleSwitchType 66 }
hpnicfevtModuleSw-BOARD-LS81FT48              OBJECT IDENTIFIER ::= { hpnicfevtModuleSwitchType 67 }
hpnicfevtModuleSw-BOARD-LS81GB8U              OBJECT IDENTIFIER ::= { hpnicfevtModuleSwitchType 68 }
hpnicfevtModuleSw-BOARD-LS81GT8U              OBJECT IDENTIFIER ::= { hpnicfevtModuleSwitchType 69 }
hpnicfevtModuleSw-BOARD-LS81FS24              OBJECT IDENTIFIER ::= { hpnicfevtModuleSwitchType 70 }
hpnicfevtModuleSw-BOARD-LS81FM24              OBJECT IDENTIFIER ::= { hpnicfevtModuleSwitchType 71 }
hpnicfevtModuleSw-BOARD-LS82GP20              OBJECT IDENTIFIER ::= { hpnicfevtModuleSwitchType 72 }
hpnicfevtModuleSw-LSB1SRPB                    OBJECT IDENTIFIER ::= { hpnicfevtModuleSwitchType 73 }
hpnicfevtModuleSw-LSB1F32GA                   OBJECT IDENTIFIER ::= { hpnicfevtModuleSwitchType 74 }
hpnicfevtModuleSw-LSB1F32GB                   OBJECT IDENTIFIER ::= { hpnicfevtModuleSwitchType 75 }
hpnicfevtModuleSw-LSB2FT48A                   OBJECT IDENTIFIER ::= { hpnicfevtModuleSwitchType 76 }
hpnicfevtModuleSw-LSB2FT48B                   OBJECT IDENTIFIER ::= { hpnicfevtModuleSwitchType 77 }
hpnicfevtModuleSw-LSB1GT12A                   OBJECT IDENTIFIER ::= { hpnicfevtModuleSwitchType 78 }
hpnicfevtModuleSw-LSB1GT12B                   OBJECT IDENTIFIER ::= { hpnicfevtModuleSwitchType 79 }
hpnicfevtModuleSw-PC4U                        OBJECT IDENTIFIER ::= { hpnicfevtModuleSwitchType 80 }
hpnicfevtModuleSw-FT32A                       OBJECT IDENTIFIER ::= { hpnicfevtModuleSwitchType 81 }
hpnicfevtModuleSw-GT4U                        OBJECT IDENTIFIER ::= { hpnicfevtModuleSwitchType 82 }
hpnicfevtModuleSw-BOARD-LS83FP20A             OBJECT IDENTIFIER ::= { hpnicfevtModuleSwitchType 83 }
hpnicfevtModuleSw-BOARD-LS82HGMU              OBJECT IDENTIFIER ::= { hpnicfevtModuleSwitchType 84 }
hpnicfevtModuleSw-LSB1GP8TB                   OBJECT IDENTIFIER ::= { hpnicfevtModuleSwitchType 85 }
hpnicfevtModuleSw-LSB1GP8TC                   OBJECT IDENTIFIER ::= { hpnicfevtModuleSwitchType 86 }
hpnicfevtModuleSw-LSB1GT8PB                   OBJECT IDENTIFIER ::= { hpnicfevtModuleSwitchType 87 }
hpnicfevtModuleSw-LSB1GT8PC                   OBJECT IDENTIFIER ::= { hpnicfevtModuleSwitchType 88 }
hpnicfevtModuleSw-LSB1FT48C                   OBJECT IDENTIFIER ::= { hpnicfevtModuleSwitchType 89 }
hpnicfevtModuleSw-LSB1FP20C                   OBJECT IDENTIFIER ::= { hpnicfevtModuleSwitchType 90 }
hpnicfevtModuleSw-LSB1F32GC                   OBJECT IDENTIFIER ::= { hpnicfevtModuleSwitchType 91 }
hpnicfevtModuleSw-LSB1GT12C                   OBJECT IDENTIFIER ::= { hpnicfevtModuleSwitchType 92 }
hpnicfevtModuleSw-LSB1GP12C                   OBJECT IDENTIFIER ::= { hpnicfevtModuleSwitchType 93 }
hpnicfevtModuleSw-LSB1P4G8C                   OBJECT IDENTIFIER ::= { hpnicfevtModuleSwitchType 94 }
hpnicfevtModuleSw-LSB1TGX1C                   OBJECT IDENTIFIER ::= { hpnicfevtModuleSwitchType 95 }
hpnicfevtModuleSw-LSB1GT24B                   OBJECT IDENTIFIER ::= { hpnicfevtModuleSwitchType 96 }
hpnicfevtModuleSw-LSB1GT24C                   OBJECT IDENTIFIER ::= { hpnicfevtModuleSwitchType 97 }
hpnicfevtModuleSw-LSB1GP24B                   OBJECT IDENTIFIER ::= { hpnicfevtModuleSwitchType 98 }
hpnicfevtModuleSw-LSB1GP24C                   OBJECT IDENTIFIER ::= { hpnicfevtModuleSwitchType 99 }
hpnicfevtModuleSw-LSB1XP2B                    OBJECT IDENTIFIER ::= { hpnicfevtModuleSwitchType 100 }
hpnicfevtModuleSw-LSB1XP2C                    OBJECT IDENTIFIER ::= { hpnicfevtModuleSwitchType 101 }
hpnicfevtModuleSw-LSB1GV48B                   OBJECT IDENTIFIER ::= { hpnicfevtModuleSwitchType 102 }
hpnicfevtModuleSw-LSB1GV48C                   OBJECT IDENTIFIER ::= { hpnicfevtModuleSwitchType 103 }
hpnicfevtModuleSw-LSB1SRPC                    OBJECT IDENTIFIER ::= { hpnicfevtModuleSwitchType 104 }
hpnicfevtModuleSw-LSB1SRP1N0                  OBJECT IDENTIFIER ::= { hpnicfevtModuleSwitchType 105 }
hpnicfevtModuleSw-LSB1SRP1N1                  OBJECT IDENTIFIER ::= { hpnicfevtModuleSwitchType 106 }
hpnicfevtModuleSw-LSB1SRP1N2                  OBJECT IDENTIFIER ::= { hpnicfevtModuleSwitchType 107 }
hpnicfevtModuleSw-GT24                        OBJECT IDENTIFIER ::= { hpnicfevtModuleSwitchType 108 }
hpnicfevtModuleSw-GP24                        OBJECT IDENTIFIER ::= { hpnicfevtModuleSwitchType 109 }
hpnicfevtModuleSw-XP2                         OBJECT IDENTIFIER ::= { hpnicfevtModuleSwitchType 110 }
hpnicfevtModuleSw-GV48                        OBJECT IDENTIFIER ::= { hpnicfevtModuleSwitchType 111 }
hpnicfevtModuleSw-LSG1GP8U                    OBJECT IDENTIFIER ::= { hpnicfevtModuleSwitchType 112 }
hpnicfevtModuleSw-LSG1GT8U                    OBJECT IDENTIFIER ::= { hpnicfevtModuleSwitchType 113 }
hpnicfevtModuleSw-LSG1TG1U                    OBJECT IDENTIFIER ::= { hpnicfevtModuleSwitchType 114 }
hpnicfevtModuleSw-LSG1TD1U                    OBJECT IDENTIFIER ::= { hpnicfevtModuleSwitchType 115 }
hpnicfevtModuleSw-LSB2FT48C                   OBJECT IDENTIFIER ::= { hpnicfevtModuleSwitchType 116 } -- 48-Ports 100Base-TX Ethernet Interface module C
hpnicfevtModuleSw-LSB1GT48B                   OBJECT IDENTIFIER ::= { hpnicfevtModuleSwitchType 117 } -- 48-Ports 10/100/1000Base-T Ethernet Interface Module B
hpnicfevtModuleSw-LSB1GT48C                   OBJECT IDENTIFIER ::= { hpnicfevtModuleSwitchType 118 } -- 48-Ports 10/100/1000Base-T Ethernet Interface Module C
hpnicfevtModuleSw-LS81GT48                    OBJECT IDENTIFIER ::= { hpnicfevtModuleSwitchType 119 } -- 48 Port Gigabit Ethernet Electric Interface Unit
hpnicfevtModuleSw-LS81SRPG0                   OBJECT IDENTIFIER ::= { hpnicfevtModuleSwitchType 120 } -- Salience III, Switch and Route Processing Board
hpnicfevtModuleSw-LS81SRPG1                   OBJECT IDENTIFIER ::= { hpnicfevtModuleSwitchType 121 } -- Salience III Plus
hpnicfevtModuleSw-LS81SRPG2                   OBJECT IDENTIFIER ::= { hpnicfevtModuleSwitchType 122 } -- Salience III Lite
hpnicfevtModuleSw-LS81SRPG3                   OBJECT IDENTIFIER ::= { hpnicfevtModuleSwitchType 123 } -- Salience III Edge
--hpnicfevtModuleSw-LS81SRPG                  OBJECT IDENTIFIER ::= { hpnicfevtModuleSwitchType 124 } Switch And Route Processing Unit, Salience III. not used.
hpnicfevtModuleSw-SR01SRPUB                   OBJECT IDENTIFIER ::= { hpnicfevtModuleSwitchType 125 } -- Switching and Route Processing Unit
hpnicfevtModuleSw-SR01SRPUA                   OBJECT IDENTIFIER ::= { hpnicfevtModuleSwitchType 126 } -- Switching and Route Processing Unit
hpnicfevtModuleSw-SR01GP12L                   OBJECT IDENTIFIER ::= { hpnicfevtModuleSwitchType 127 } -- 12-Port 1000Base-X Ethernet SFP Optical Interface Line Card(L)
hpnicfevtModuleSw-SR01GP12W                   OBJECT IDENTIFIER ::= { hpnicfevtModuleSwitchType 128 } -- 12-Port 1000Base-X Ethernet SFP Optical Interface Line Card(W)
hpnicfevtModuleSw-SR01FT48L                   OBJECT IDENTIFIER ::= { hpnicfevtModuleSwitchType 129 } -- 48-Port 10/100Base-TX Ethernet RJ45 Electrical Interface Line Card (L)
hpnicfevtModuleSw-SR01FT48W                   OBJECT IDENTIFIER ::= { hpnicfevtModuleSwitchType 130 } -- 48-Port 10/100Base-TX Ethernet RJ45 Electrical Interface Line Card (W)
hpnicfevtModuleSw-SR01XK1W                    OBJECT IDENTIFIER ::= { hpnicfevtModuleSwitchType 131 } -- 1-Port 10GBase-R Ethernet XENPAK Optical Interface Line Card (W)
hpnicfevtModuleSw-SR01FP20W                   OBJECT IDENTIFIER ::= { hpnicfevtModuleSwitchType 132 } -- 20-Port 100Base-FX Ethernet SFP Optical Interface Line Card (W)
hpnicfevtModuleSw-SR01GT12W                   OBJECT IDENTIFIER ::= { hpnicfevtModuleSwitchType 133 } -- 12-Port 10/100/1000Base-T Ethernet RJ45 Electrical Interface Line Card (W)
hpnicfevtModuleSw-SR01F32GL                   OBJECT IDENTIFIER ::= { hpnicfevtModuleSwitchType 134 } -- 32-Port 10/100Base-TX Ethernet RJ45 Electrical Interface + 4-Port 1000Base-X Ethernet SFP Optical interface Line Card (L)
hpnicfevtModuleSw-SR01F32GW                   OBJECT IDENTIFIER ::= { hpnicfevtModuleSwitchType 135 } -- 32-Port 10/100Base-TX Ethernet RJ45 Electrical Interface  + 4-Port 1000Base-X  Ethernet SFP Optical interface Line Card (W)
hpnicfevtModuleSw-SR01GT8PL                   OBJECT IDENTIFIER ::= { hpnicfevtModuleSwitchType 136 } -- 8-Port 10/100/1000Base-T Ethernet RJ45 Electrical Interface + 4-Port 1000Base-X Ethernet SFP Optical Line Card (L)
hpnicfevtModuleSw-SR01GT8PW                   OBJECT IDENTIFIER ::= { hpnicfevtModuleSwitchType 137 } -- 8-Port 10/100/1000Base-T Ethernet RJ45 Electrical Interface + 4-Port 1000Base-X Ethernet SFP Optical Line Card (W)
hpnicfevtModuleSw-SR01P4G8W                   OBJECT IDENTIFIER ::= { hpnicfevtModuleSwitchType 138 } -- 4-Port 155M POS Optical Interface + 8-Port 1000Base-X Ethernet SFP Optical Interface Line Card (W)
hpnicfevtModuleSw-LSA1FP8U                    OBJECT IDENTIFIER ::= { hpnicfevtModuleSwitchType 139 } -- 8 Ports 100Base-FX Ethernet SFP Card
hpnicfevtModuleSw-LSB1SP4B                    OBJECT IDENTIFIER ::= { hpnicfevtModuleSwitchType 140 } -- 4-Port OC-48 POS SFP Optical Interface Board B
hpnicfevtModuleSw-LSB1SP4C                    OBJECT IDENTIFIER ::= { hpnicfevtModuleSwitchType 141 } -- 4-Port OC-48 POS SFP Optical Interface Board C
hpnicfevtModuleSw-LSB1UP1B                    OBJECT IDENTIFIER ::= { hpnicfevtModuleSwitchType 142 } -- 1-Port OC-192 POS XFP Optical Interface Board B
hpnicfevtModuleSw-LSB1UP1C                    OBJECT IDENTIFIER ::= { hpnicfevtModuleSwitchType 143 } -- 1-Port OC-192 POS XFP Optical Interface Board C
hpnicfevtModuleSw-LSB1XP4B                    OBJECT IDENTIFIER ::= { hpnicfevtModuleSwitchType 144 } -- 4-Port 10GBase Ethernet XFP Optical Interface Board B
hpnicfevtModuleSw-LSB1XP4C                    OBJECT IDENTIFIER ::= { hpnicfevtModuleSwitchType 145 } -- 4-Port 10GBase Ethernet XFP Optical Interface Board C
hpnicfevtModuleSw-SP4                         OBJECT IDENTIFIER ::= { hpnicfevtModuleSwitchType 146 } -- 4-Port OC-48 POS SFP Optical Interface Module
hpnicfevtModuleSw-UP1                         OBJECT IDENTIFIER ::= { hpnicfevtModuleSwitchType 147 } -- 1-Port OC-192 POS XFP Optical Interface Module
hpnicfevtModuleSw-XP4                         OBJECT IDENTIFIER ::= { hpnicfevtModuleSwitchType 148 } -- 4-Port 10GBase Ethernet XFP Optical Interface Module
hpnicfevtModuleSw-LS81VSNP                    OBJECT IDENTIFIER ::= { hpnicfevtModuleSwitchType 149 } -- VerSatile Network Processing Board
hpnicfevtModuleSw-LS81T12P                    OBJECT IDENTIFIER ::= { hpnicfevtModuleSwitchType 150 } -- 12-Port 1000Base-T Gigabit Ethernet Interface(RJ45)+4-Port 1000BASE-X  Gigabit Ethernet Optical Interface Board(SFP,LC)
hpnicfevtModuleSw-LS81P12T                    OBJECT IDENTIFIER ::= { hpnicfevtModuleSwitchType 151 } -- 12-Port 1000BASE-X Gigabit Ethernet Optical Interface(SFP,LC)+4-Port 1000BASE-T Gigabit Ethernet Interface Board(RJ45)
hpnicfevtModuleSw-LS81GP8UB                   OBJECT IDENTIFIER ::= { hpnicfevtModuleSwitchType 152 } -- 8-Port 1000M Ethernet Optical Interface Board(SFP,LC),LC Connector
hpnicfevtModuleSw-LS81FT48E                   OBJECT IDENTIFIER ::= { hpnicfevtModuleSwitchType 153 } -- 48-Port 100M Ethernet Electrical Interface Switch Unit(RJ45)
hpnicfevtModuleSw-LS81GP4UB                   OBJECT IDENTIFIER ::= { hpnicfevtModuleSwitchType 154 } -- 4-Port 1000M Ethernet Optical Interface Board(SFP,LC)
hpnicfevtModuleSw-LS81GT8UE                   OBJECT IDENTIFIER ::= { hpnicfevtModuleSwitchType 155 } -- 8-Port 1000M Ethernet Electrical Interface Switch Unit (RJ45)
hpnicfevtModuleSw-LS81GT48A                   OBJECT IDENTIFIER ::= { hpnicfevtModuleSwitchType 156 } -- 48 Port Gigabit Ethernet Electric Interface Unit
hpnicfevtModuleSw-LS81FP48                    OBJECT IDENTIFIER ::= { hpnicfevtModuleSwitchType 157 } -- 48 Port 100M Ethernet Optical Interface Board(SFP,LC)
hpnicfevtModuleSw-LSB1XK1B                    OBJECT IDENTIFIER ::= { hpnicfevtModuleSwitchType 158 } -- 1-Port 10GBase-R Ethernet XENPAK Optical Interface Board B
hpnicfevtModuleSw-LSB1XK1C                    OBJECT IDENTIFIER ::= { hpnicfevtModuleSwitchType 159 } -- 1-Port 10GBase-R Ethernet XENPAK Optical Interface Board C
hpnicfevtModuleSw-SR01SRPUC                   OBJECT IDENTIFIER ::= { hpnicfevtModuleSwitchType 160 } -- Switching and Route Processing Unit C
hpnicfevtModuleSw-SR01SRPUD                   OBJECT IDENTIFIER ::= { hpnicfevtModuleSwitchType 161 } -- Switching and Route Processing Unit D
hpnicfevtModuleSw-SR01SRPUE                   OBJECT IDENTIFIER ::= { hpnicfevtModuleSwitchType 162 } -- Switching and Route Processing Unit E
hpnicfevtModuleSw-LSB1SRP1N3                  OBJECT IDENTIFIER ::= { hpnicfevtModuleSwitchType 163 } -- Switching and Route Process Unit, Clock Module
hpnicfevtModuleSw-LSB1VP2B                    OBJECT IDENTIFIER ::= { hpnicfevtModuleSwitchType 164 } -- 2*10G Resilient Packet Ring Interface Line Card
hpnicfevtModuleSw-LSB1NATB                    OBJECT IDENTIFIER ::= { hpnicfevtModuleSwitchType 165 } -- NAT Service Processing Card (B)
hpnicfevtModuleSw-LSB1VPNB                    OBJECT IDENTIFIER ::= { hpnicfevtModuleSwitchType 166 } -- VPN Service Processing Card (B)
hpnicfevtModuleSw-LSGP8P                      OBJECT IDENTIFIER ::= { hpnicfevtModuleSwitchType 167 } -- 8-Port 1000M SFP Module
hpnicfevtModuleSw-LSXK1P                      OBJECT IDENTIFIER ::= { hpnicfevtModuleSwitchType 168 } -- 1-Port 10G Xenpak Module
hpnicfevtModuleSw-LSXP2P                      OBJECT IDENTIFIER ::= { hpnicfevtModuleSwitchType 169 } -- 2-Port 10G XFP Module
hpnicfevtModuleSw-LS81FT48F                   OBJECT IDENTIFIER ::= { hpnicfevtModuleSwitchType 170 } -- 48-Port 100M Ethernet Electrical Interface Switch Unit(RJ45)
hpnicfevtModuleSw-LS81PT8G                    OBJECT IDENTIFIER ::= { hpnicfevtModuleSwitchType 171 } -- 8 Port 1000BASE-X Gigabit Passive Optical Line Interface Board
hpnicfevtModuleSw-LS81PT4G                    OBJECT IDENTIFIER ::= { hpnicfevtModuleSwitchType 172 } -- 4 Port 1000BASE-X Gigabit Passive Optical Line Interface Board
hpnicfevtModuleSw-LSSTK24G                    OBJECT IDENTIFIER ::= { hpnicfevtModuleSwitchType 173 } -- 24G Stacking Ports Module
hpnicfevtModuleSw-LS82GT20A                   OBJECT IDENTIFIER ::= { hpnicfevtModuleSwitchType 174 } -- 20-Port 1000Base-T Gigabit Ethernet Electrical Interface Board(RJ45), BCM5697
hpnicfevtModuleSw-LS82GP20A                   OBJECT IDENTIFIER ::= { hpnicfevtModuleSwitchType 175 } -- 20-Port 1000BASE-X Gigabit Ethernet Optical Interface Board(SFP,LC), BCM5697
hpnicfevtModuleSw-LS81TGX1C                   OBJECT IDENTIFIER ::= { hpnicfevtModuleSwitchType 176 } -- 1-Port 10G Base-R Ethernet Board
hpnicfevtModuleSw-VP2                         OBJECT IDENTIFIER ::= { hpnicfevtModuleSwitchType 177 } -- 2*10G Resilient Packet Ring Interface Module
hpnicfevtModuleSw-LSA1FB8U                    OBJECT IDENTIFIER ::= { hpnicfevtModuleSwitchType 178 } -- 8-Port 100Base-Fx BIDI Ethernet Board
hpnicfevtModuleSw-LS81T12PE                   OBJECT IDENTIFIER ::= { hpnicfevtModuleSwitchType 179 } -- 12-Port 1000Base-T GE Interface+4-Port 1000BASE-X GE Optical Interface Board(SFP,LC)
hpnicfevtModuleSw-LS81P12TE                   OBJECT IDENTIFIER ::= { hpnicfevtModuleSwitchType 180 } -- 12-Port 1000BASE-X GE Optical Interface(SFP,LC)+4-Port 1000 BASE-T GE Interface Board(RJ45)
hpnicfevtModuleSw-LSB1SRP2N0                  OBJECT IDENTIFIER ::= { hpnicfevtModuleSwitchType 181 } -- Switching and Route Process Unit,12*LPU
hpnicfevtModuleSw-LSB1SRP2N3                  OBJECT IDENTIFIER ::= { hpnicfevtModuleSwitchType 182 } -- Switching and Route Process Unit, Clock Module
hpnicfevtModuleSw-LSB1GV48DB                  OBJECT IDENTIFIER ::= { hpnicfevtModuleSwitchType 183 } -- 48 Ports 1000Base-T Ethernet Interface Line Card with POE(DB)
hpnicfevtModuleSw-LSB1FW8B                    OBJECT IDENTIFIER ::= { hpnicfevtModuleSwitchType 184 } -- Firewall Service Processing Board with 8GE (B)
hpnicfevtModuleSw-LSB1IPSEC8B                 OBJECT IDENTIFIER ::= { hpnicfevtModuleSwitchType 185 } -- VPN Service Processing Board with 8GE (B)
hpnicfevtModuleSw-LSB1IDSB                    OBJECT IDENTIFIER ::= { hpnicfevtModuleSwitchType 186 } -- IDS Service Processing Board (B)
hpnicfevtModuleSw-LSB1IPSB                    OBJECT IDENTIFIER ::= { hpnicfevtModuleSwitchType 187 } -- IPS Service Processing Board (B)
hpnicfevtModuleSw-LSB2FT48CA                  OBJECT IDENTIFIER ::= { hpnicfevtModuleSwitchType 188 } -- 48 Ports 100Base-TX Ethernet Line Card (CA)
hpnicfevtModuleSw-LSB1FP20CA                  OBJECT IDENTIFIER ::= { hpnicfevtModuleSwitchType 189 } -- 20 Ports 100Base-FX Ethernet Interface Service Card (CA)
hpnicfevtModuleSw-LSB1F32GCA                  OBJECT IDENTIFIER ::= { hpnicfevtModuleSwitchType 190 } -- 32 Ports FE and 4 Ports GE Line Card(CA)
hpnicfevtModuleSw-LSB1P4G8CA                  OBJECT IDENTIFIER ::= { hpnicfevtModuleSwitchType 191 } -- 4 Ports OC-3c POS and 8 Ports GE Line Card(CA)
hpnicfevtModuleSw-LSB1GT12CA                  OBJECT IDENTIFIER ::= { hpnicfevtModuleSwitchType 192 } -- 12 Ports 1000Base-T Ethernet Interface Line Card(CA)
hpnicfevtModuleSw-LSB1GT24CA                  OBJECT IDENTIFIER ::= { hpnicfevtModuleSwitchType 193 } -- 24 Ports 1000Base-T Ethernet Interface Line Card(CA)
hpnicfevtModuleSw-LSB1GP12CA                  OBJECT IDENTIFIER ::= { hpnicfevtModuleSwitchType 194 } -- 12 Ports 1000Base Ethernet Optical Interface Service Card(CA)
hpnicfevtModuleSw-LSB1GP24CA                  OBJECT IDENTIFIER ::= { hpnicfevtModuleSwitchType 195 } -- 24 Ports 1000Base-X Ethernet Interface Line Card (CA)
hpnicfevtModuleSw-LSB1GT8PCA                  OBJECT IDENTIFIER ::= { hpnicfevtModuleSwitchType 196 } -- 8 Ports 1000Base-T Ethernet Interface & 4 Ports 1000Base-X Ethernet SFP Interface Line Card(CA)
hpnicfevtModuleSw-LSB1XP2CA                   OBJECT IDENTIFIER ::= { hpnicfevtModuleSwitchType 197 } -- 2-Port 10GBase-R/W Ethernet XFP Optical Interface Card(CA)
hpnicfevtModuleSw-LSB1XK1CA                   OBJECT IDENTIFIER ::= { hpnicfevtModuleSwitchType 198 } -- 10GBase-R Ethernet XENPAK Optical Interface Line Card(CA)
hpnicfevtModuleSw-LSB1XP4CA                   OBJECT IDENTIFIER ::= { hpnicfevtModuleSwitchType 199 } -- 4-Port 10GBase-R/X Ethernet Optical Interface Line Card(CA)
hpnicfevtModuleSw-LSB1UP1CA                   OBJECT IDENTIFIER ::= { hpnicfevtModuleSwitchType 200 } -- Single Port OC-192c POS XFP Optical Interface Card(CA)
hpnicfevtModuleSw-LSB1SP4CA                   OBJECT IDENTIFIER ::= { hpnicfevtModuleSwitchType 201 } -- 4-Port OC-48c POS SFP Optical Interface Card(CA)
hpnicfevtModuleSw-LSB1VP2CA                   OBJECT IDENTIFIER ::= { hpnicfevtModuleSwitchType 202 } -- 2*10G RPR Process Unit(CA)
hpnicfevtModuleSw-SR01FT48WA                  OBJECT IDENTIFIER ::= { hpnicfevtModuleSwitchType 203 } -- 48 Ports 100Base-TX Ethernet Line Card (WA)
hpnicfevtModuleSw-SR01FP20WA                  OBJECT IDENTIFIER ::= { hpnicfevtModuleSwitchType 204 } -- 20 Ports 100Base-FX Ethernet Interface Service Card (WA)
hpnicfevtModuleSw-SR01F32GWA                  OBJECT IDENTIFIER ::= { hpnicfevtModuleSwitchType 205 } -- 32 Ports FE and 4 Ports GE Line Card(WA)
hpnicfevtModuleSw-SR01P4G8WA                  OBJECT IDENTIFIER ::= { hpnicfevtModuleSwitchType 206 } -- 4 Ports OC-3c POS and 8 Ports GE Line Card(WA)
hpnicfevtModuleSw-SR01GT12WA                  OBJECT IDENTIFIER ::= { hpnicfevtModuleSwitchType 207 } -- 12 Ports 1000Base-T Ethernet Interface Line Card(WA)
hpnicfevtModuleSw-SR01GT24WA                  OBJECT IDENTIFIER ::= { hpnicfevtModuleSwitchType 208 } -- 24 Ports 1000Base-T Ethernet Interface Line Card(WA)
hpnicfevtModuleSw-SR01GP12WA                  OBJECT IDENTIFIER ::= { hpnicfevtModuleSwitchType 209 } -- 12 Ports 1000Base Ethernet Optical Interface Service Card(WA)
hpnicfevtModuleSw-SR01GP24WA                  OBJECT IDENTIFIER ::= { hpnicfevtModuleSwitchType 210 } -- 24 Ports 1000Base-X Ethernet Interface Line Card (WA)
hpnicfevtModuleSw-SR01GT8PWA                  OBJECT IDENTIFIER ::= { hpnicfevtModuleSwitchType 211 } -- 8 Ports 1000Base-T Ethernet Interface & 4 Ports 1000Base-X Ethernet SFP Interface Line Card(WA)
hpnicfevtModuleSw-SR01XP2WA                   OBJECT IDENTIFIER ::= { hpnicfevtModuleSwitchType 212 } -- 2-Port 10GBase-R/W Ethernet XFP Optical Interface Card(WA)
hpnicfevtModuleSw-SR01XK1WA                   OBJECT IDENTIFIER ::= { hpnicfevtModuleSwitchType 213 } -- 10GBase-R Ethernet XENPAK Optical Interface Line Card(WA)
hpnicfevtModuleSw-SR01UP1WA                   OBJECT IDENTIFIER ::= { hpnicfevtModuleSwitchType 214 } -- Single Port OC-192c POS XFP Optical Interface Card(WA)
hpnicfevtModuleSw-SR01SP4WA                   OBJECT IDENTIFIER ::= { hpnicfevtModuleSwitchType 215 } -- 4-Port OC-48c POS SFP Optical Interface Card(WA)
hpnicfevtModuleSw-GP8U                        OBJECT IDENTIFIER ::= { hpnicfevtModuleSwitchType 216 } -- 8-Port 1000Base-X SFP Optical Interface Module
hpnicfevtModuleSw-LSEXP1P                     OBJECT IDENTIFIER ::= { hpnicfevtModuleSwitchType 217 } -- Single 10G SFP Optical Interface Module
hpnicfevtModuleSw-LSEXK1P                     OBJECT IDENTIFIER ::= { hpnicfevtModuleSwitchType 218 } -- Single 10G XENPAK Interface Module
hpnicfevtModuleSw-LSEXS1P                     OBJECT IDENTIFIER ::= { hpnicfevtModuleSwitchType 219 } -- Single 10G STACK Interface Module
hpnicfevtModuleSw-LS81GP48                    OBJECT IDENTIFIER ::= { hpnicfevtModuleSwitchType 220 } -- 48-Port 1000M Ethernet Optical Interface Board(SFP,LC),LC Connector
hpnicfevtModuleSw-LS81GT48B                   OBJECT IDENTIFIER ::= { hpnicfevtModuleSwitchType 221 } -- 48-Port 1000Base-T Gigabit Ethernet Interface Board(RJ45)
hpnicfevtModuleSw-LS81T16P                    OBJECT IDENTIFIER ::= { hpnicfevtModuleSwitchType 222 } -- 16-Port 1000Base-T Gigabit Ethernet Interface(RJ45) + 8-Port 1000BASE-X Gigabit Ethernet Optical Interface Board(SFP,LC)
hpnicfevtModuleSw-LS81T32P                    OBJECT IDENTIFIER ::= { hpnicfevtModuleSwitchType 223 } -- 32-Port 1000Base-T Gigabit Ethernet Interface(RJ45) + 16-Port 1000BASE-X Gigabit Ethernet Optical Interface Board(SFP,LC)
hpnicfevtModuleSw-LS81TGX2                    OBJECT IDENTIFIER ::= { hpnicfevtModuleSwitchType 224 } -- 2-Port 10GBASE Ethernet Interface Board(XFP,LC)
hpnicfevtModuleSw-LS81TGX4                    OBJECT IDENTIFIER ::= { hpnicfevtModuleSwitchType 225 } -- 4-Port 10GBASE Ethernet Interface Module(XFP,LC),XG
hpnicfevtModuleSw-LSB1GV48DA                  OBJECT IDENTIFIER ::= { hpnicfevtModuleSwitchType 226 } -- 48 Ports 1000Base-T Ethernet Interface Line Card with POE(DA)
hpnicfevtModuleSw-SR01GV48VB                  OBJECT IDENTIFIER ::= { hpnicfevtModuleSwitchType 227 } -- 48 Ports 1000Base-T Ethernet Interface Line Card with POE(VB)
hpnicfevtModuleSw-LSB1GT24DB                  OBJECT IDENTIFIER ::= { hpnicfevtModuleSwitchType 228 } -- 24 Ports 1000Base-T Ethernet Interface Line Card(DB)
hpnicfevtModuleSw-LSB1GP24DB                  OBJECT IDENTIFIER ::= { hpnicfevtModuleSwitchType 229 } -- 24 Ports 1000Base-X Ethernet Interface Line Card(DB)
hpnicfevtModuleSw-LSB1GP24DC                  OBJECT IDENTIFIER ::= { hpnicfevtModuleSwitchType 230 } -- 24 Ports 1000Base-X Ethernet Interface Line Card(DC)
hpnicfevtModuleSw-LSB1FW8DB                   OBJECT IDENTIFIER ::= { hpnicfevtModuleSwitchType 231 } -- 8-port 1000BASE-X (SFP) Firewall Service Card(DB)
hpnicfevtModuleSw-LSB1IPSEC8DB                OBJECT IDENTIFIER ::= { hpnicfevtModuleSwitchType 232 } -- 8-port 1000BASE-X (SFP) IPSEC Service Card(DB)
hpnicfevtModuleSw-SR01GT24VB                  OBJECT IDENTIFIER ::= { hpnicfevtModuleSwitchType 233 } -- 24 Ports 1000Base-T Ethernet Interface Line Card(VB)
hpnicfevtModuleSw-SR01GP24VC                  OBJECT IDENTIFIER ::= { hpnicfevtModuleSwitchType 234 } -- 24 Ports 1000Base-X Ethernet Interface Line Card(VC)
hpnicfevtModuleSw-SR01VP2WA                   OBJECT IDENTIFIER ::= { hpnicfevtModuleSwitchType 235 } -- 2*10G RPR Process Unit(WA)
hpnicfevtModuleSw-SR01FW8VB                   OBJECT IDENTIFIER ::= { hpnicfevtModuleSwitchType 236 } -- 8-port 1000BASE-X (SFP) Firewall Service Card(VB)
hpnicfevtModuleSw-SR01IPSEC8VB                OBJECT IDENTIFIER ::= { hpnicfevtModuleSwitchType 237 } -- 8-port 1000BASE-X (SFP) IPSEC Service Card(VB)
hpnicfevtModuleSw-SR01NATL                    OBJECT IDENTIFIER ::= { hpnicfevtModuleSwitchType 238 } -- NAT Service Processing Card (L)
hpnicfevtModuleSw-SR01VPNL                    OBJECT IDENTIFIER ::= { hpnicfevtModuleSwitchType 239 } -- VPN Service Processing Card (L)
hpnicfevtModuleSw-LSB1GP24CB                  OBJECT IDENTIFIER ::= { hpnicfevtModuleSwitchType 240 } -- 24 Ports 1000Base-X Ethernet Interface Line Card(CB)
hpnicfevtModuleSw-LSB1GP48DB                  OBJECT IDENTIFIER ::= { hpnicfevtModuleSwitchType 241 } -- 48-Port Gigabit Ethernet Optical Interface Line Card(DB)
hpnicfevtModuleSw-LSB1XP2CB                   OBJECT IDENTIFIER ::= { hpnicfevtModuleSwitchType 242 } -- 2-Port 10Gigabit Ethernet Optical Interface Card(CB)
hpnicfevtModuleSw-XP4L                        OBJECT IDENTIFIER ::= { hpnicfevtModuleSwitchType 243 } -- 4 Port 1000BASE Optic Interface Module (XFP)
hpnicfevtModuleSw-LSB1XP4LDB                  OBJECT IDENTIFIER ::= { hpnicfevtModuleSwitchType 244 } -- 4-Port 10GBase-R/W Ethernet XFP Optical Interface Line Speed Card(DB)
hpnicfevtModuleSw-LSB1XP4LDC                  OBJECT IDENTIFIER ::= { hpnicfevtModuleSwitchType 245 } -- 4-Port 10GBase-R/W Ethernet XFP Optical Interface Line Speed Card(DC)
hpnicfevtModuleSw-AHP4                        OBJECT IDENTIFIER ::= { hpnicfevtModuleSwitchType 246 } -- 2-Port OC-3 ATM and 2-Port OC-3/12 ATM Interface Module (SFP)
hpnicfevtModuleSw-LSB1AHP4GCA                 OBJECT IDENTIFIER ::= { hpnicfevtModuleSwitchType 247 } -- 2-Port OC-3 ATM and 2-Port OC-3/12 ATM and 8-Port 1000Base-X Ethernet Optical Interface Line Card(CA)
hpnicfevtModuleSw-CLP4                        OBJECT IDENTIFIER ::= { hpnicfevtModuleSwitchType 248 } -- 4 Ports OC-3/STM-1 CPOS Optical Interface Module (SFP)
hpnicfevtModuleSw-LSB1CLP4GCA                 OBJECT IDENTIFIER ::= { hpnicfevtModuleSwitchType 249 } -- 4 Ports OC-3/STM-1 CPOS Optical Interface and 4-Port 1000Base-X Ethernet Optical Interface Line Card(CA)
hpnicfevtModuleSw-ET32                        OBJECT IDENTIFIER ::= { hpnicfevtModuleSwitchType 250 } -- 32-Port Channelized E1/T1 Interface Module
hpnicfevtModuleSw-LSB1ET32GCA                 OBJECT IDENTIFIER ::= { hpnicfevtModuleSwitchType 251 } -- 32-Port Channelized E1/T1 Interface and 4-Port 1000Base-X Ethernet Optical Interface Line Card(CA)
hpnicfevtModuleSw-LSB1IDSDB                   OBJECT IDENTIFIER ::= { hpnicfevtModuleSwitchType 252 } -- Intrusion Detection Service Card(DB)
hpnicfevtModuleSw-LSB1SRP2N1                  OBJECT IDENTIFIER ::= { hpnicfevtModuleSwitchType 253 } -- Switching and Route Processing Board,8*LPU
hpnicfevtModuleSw-BOARD-LS82SRPB              OBJECT IDENTIFIER ::= { hpnicfevtModuleSwitchType 254 }
hpnicfevtModuleSw-BORAD-LS83SRPC              OBJECT IDENTIFIER ::= { hpnicfevtModuleSwitchType 255 }
hpnicfevtModuleSw-Main                        OBJECT IDENTIFIER ::= { hpnicfevtModuleSwitchType 256 }
hpnicfevtModuleSw-LSB1SRP2N2                  OBJECT IDENTIFIER ::= { hpnicfevtModuleSwitchType 257 } -- Switching and Route Processing Board,5*LPU
hpnicfevtModuleSw-LSB1NAMB                    OBJECT IDENTIFIER ::= { hpnicfevtModuleSwitchType 258 } -- NAM Service Processing Card (B)
hpnicfevtModuleSw-RSP2                        OBJECT IDENTIFIER ::= { hpnicfevtModuleSwitchType 259 } -- 2*2.5G Resilient Packet Ring Interface
hpnicfevtModuleSw-LSB1RSP2CA                  OBJECT IDENTIFIER ::= { hpnicfevtModuleSwitchType 260 } -- 2*2.5G Resilient Packet Ring Interface Line Card(CA)
hpnicfevtModuleSw-SR01XP4LVC                  OBJECT IDENTIFIER ::= { hpnicfevtModuleSwitchType 261 } -- 4-Port 10GBase-R/W Ethernet XFP Optical Interface Line Speed Card(VC)
hpnicfevtModuleSw-SR01AHP4GWA                 OBJECT IDENTIFIER ::= { hpnicfevtModuleSwitchType 262 } -- 2-Port OC-3 ATM and 2-Port OC-3/12 ATM and 8-Port 1000Base-X Ethernet Optical Interface Line Card(WA)
hpnicfevtModuleSw-SR01CLP4GWA                 OBJECT IDENTIFIER ::= { hpnicfevtModuleSwitchType 263 } -- 4 Ports OC-3/STM-1 CPOS Optical Interface and 4-Port 1000Base-X Ethernet Optical Interface Line Card(WA)
hpnicfevtModuleSw-SR01ET32GWA                 OBJECT IDENTIFIER ::= { hpnicfevtModuleSwitchType 264 } -- 32-Port Channelized E1/T1 Interface and 4-Port 1000Base-X Ethernet Optical Interface Line Card(WA)
hpnicfevtModuleSw-SR01IDSVB                   OBJECT IDENTIFIER ::= { hpnicfevtModuleSwitchType 265 } -- Intrusion Detection Service Card(VB)
hpnicfevtModuleSw-SR01SRPUF                   OBJECT IDENTIFIER ::= { hpnicfevtModuleSwitchType 266 } -- Switching and Route Processing Board,12*LPU
hpnicfevtModuleSw-SR01NAML                    OBJECT IDENTIFIER ::= { hpnicfevtModuleSwitchType 267 } -- NAM Service Processing Card (L)
hpnicfevtModuleSw-SR01RSP2WA                  OBJECT IDENTIFIER ::= { hpnicfevtModuleSwitchType 268 } -- 2*2.5G Resilient Packet Ring Interface Line Card(WA)
hpnicfevtModuleSw-LSPM1XP1P                   OBJECT IDENTIFIER ::= { hpnicfevtModuleSwitchType 269 } -- 1-Port 10G XFP Module
hpnicfevtModuleSw-LSPM1XP2P                   OBJECT IDENTIFIER ::= { hpnicfevtModuleSwitchType 270 } -- 2-Port 10G XFP Module
hpnicfevtModuleSw-LSPM1CX2P                   OBJECT IDENTIFIER ::= { hpnicfevtModuleSwitchType 271 } -- 2-Port 10G CX4 Module
hpnicfevtModuleSw-STK-1000BASE-T              OBJECT IDENTIFIER ::= { hpnicfevtModuleSwitchType 272 } -- Single Port 1000BASE-T Stack Ethernet Interface Card

--
-- 273 to 299 reserved for other product
--


--
-- 300 to 499 reserved for advanced switches part I
--
hpnicfevtModuleSw-LSB1SRP1M0                  OBJECT IDENTIFIER ::= { hpnicfevtModuleSwitchType 300 } -- Switching and Route Process Unit,2*LPU or 3*LPU
hpnicfevtModuleSw-LSB1SRP1M1                  OBJECT IDENTIFIER ::= { hpnicfevtModuleSwitchType 301 } -- Switching and Route Process Unit
hpnicfevtModuleSw-LSB1GP12DB                  OBJECT IDENTIFIER ::= { hpnicfevtModuleSwitchType 302 } -- 12 Ports 1000Base Ethernet Optical Interface Service Card(DB)
hpnicfevtModuleSw-LSB1GT12DB                  OBJECT IDENTIFIER ::= { hpnicfevtModuleSwitchType 303 } -- 12 Ports 1000Base-T Ethernet Interface Line Card(DB)
hpnicfevtModuleSw-LSB1XK1DB                   OBJECT IDENTIFIER ::= { hpnicfevtModuleSwitchType 304 } -- 10GBase-R Ethernet XENPAK Optical Interface Line Card(DB)
hpnicfevtModuleSw-LSB1XP2DB                   OBJECT IDENTIFIER ::= { hpnicfevtModuleSwitchType 305 } -- 2-Port 10GBase-R/W Ethernet XFP Optical Interface Card(DB)
hpnicfevtModuleSw-LSB1XP2DC                   OBJECT IDENTIFIER ::= { hpnicfevtModuleSwitchType 306 } -- 2-Port 10GBase-R/W Ethernet XFP Optical Interface Card(DC)
hpnicfevtModuleSw-LSB1GT48LDB                 OBJECT IDENTIFIER ::= { hpnicfevtModuleSwitchType 307 } -- 48-Port Gigabit Ethernet RJ45 Electrical Interface Card (DB)
hpnicfevtModuleSw-LSB1XP4TDB                  OBJECT IDENTIFIER ::= { hpnicfevtModuleSwitchType 308 } -- 4-Port 10GBase-R/W Ethernet XFP Optical Interface Line Speed Test Card(DB)
hpnicfevtModuleSw-LSB1XP4TDC                  OBJECT IDENTIFIER ::= { hpnicfevtModuleSwitchType 309 } -- 4-Port 10GBase-R/W Ethernet XFP Optical Interface Line Speed Test Card(DC)
hpnicfevtModuleSw-LSB1RSP2DC                  OBJECT IDENTIFIER ::= { hpnicfevtModuleSwitchType 310 } -- 2*2.5G Resilient Packet Ring Interface Line Card(DC)
hpnicfevtModuleSw-LSB1VP2DC                   OBJECT IDENTIFIER ::= { hpnicfevtModuleSwitchType 311 } -- 2*10G Resilient Packet Ring Process Unit(DC)
hpnicfevtModuleSw-LSB1XP4DB                   OBJECT IDENTIFIER ::= { hpnicfevtModuleSwitchType 312 } -- 4-Port 10GBase-R/X Ethernet Optical Interface Line Card(DB)
hpnicfevtModuleSw-LSB1SRP2E0                  OBJECT IDENTIFIER ::= { hpnicfevtModuleSwitchType 313 } -- Switching and Route Process Unit,12*LPU
hpnicfevtModuleSw-LSB1SRP2E1                  OBJECT IDENTIFIER ::= { hpnicfevtModuleSwitchType 314 } -- Switching and Route Process Unit,8*LPU
hpnicfevtModuleSw-LSB1SRP2E2                  OBJECT IDENTIFIER ::= { hpnicfevtModuleSwitchType 315 } -- Switching and Route Process Unit,5*LPU
hpnicfevtModuleSw-LSB1SRP2E3                  OBJECT IDENTIFIER ::= { hpnicfevtModuleSwitchType 316 } -- Switching and Route Process Unit, Clock module
hpnicfevtModuleSw-SR01SRPUQ                   OBJECT IDENTIFIER ::= { hpnicfevtModuleSwitchType 317 } -- Switching and Route Processing Unit Q
hpnicfevtModuleSw-AHP1                        OBJECT IDENTIFIER ::= { hpnicfevtModuleSwitchType 318 } -- 1-Port OC-12c(3c)/STM-4(1) ATM Optical Interface Module(SFP)
hpnicfevtModuleSw-AHP2                        OBJECT IDENTIFIER ::= { hpnicfevtModuleSwitchType 319 } -- 2-Port OC-12c(3c)/STM-4(1) ATM Optical Interface Module(SFP)
hpnicfevtModuleSw-CLP1                        OBJECT IDENTIFIER ::= { hpnicfevtModuleSwitchType 320 } -- 1-Port OC-3/STM-1 CPOS Optical Interface Module(SFP)
hpnicfevtModuleSw-CLP2                        OBJECT IDENTIFIER ::= { hpnicfevtModuleSwitchType 321 } -- 2-Port OC-3/STM-1 CPOS Optical Interface Module(SFP)
hpnicfevtModuleSw-ET16                        OBJECT IDENTIFIER ::= { hpnicfevtModuleSwitchType 322 } -- 16-Port Channelized E1/T1 Interface Module
hpnicfevtModuleSw-LSB1SRP1NA0                 OBJECT IDENTIFIER ::= { hpnicfevtModuleSwitchType 323 } -- Switching and Route Process Unit,12*LPU
hpnicfevtModuleSw-LSB1SRP1NA1                 OBJECT IDENTIFIER ::= { hpnicfevtModuleSwitchType 324 } -- Switching and Route Process Unit,8*LPU
hpnicfevtModuleSw-LSB1SRP1NA2                 OBJECT IDENTIFIER ::= { hpnicfevtModuleSwitchType 325 } -- Switching and Route Process Unit,5*LPU
hpnicfevtModuleSw-LSB1SRP1NA3                 OBJECT IDENTIFIER ::= { hpnicfevtModuleSwitchType 326 } -- Switching and Route Process Unit, Clock module
hpnicfevtModuleSw-SR01AHP1GWA                 OBJECT IDENTIFIER ::= { hpnicfevtModuleSwitchType 327 } -- 1-Port OC-12c(3c)/STM-4(1) ATM Optical Interface and 4-Port 1000Base-X Ethernet Optical Interface Line Card(WA)
hpnicfevtModuleSw-SR01AHP2GWA                 OBJECT IDENTIFIER ::= { hpnicfevtModuleSwitchType 328 } -- 2-Port OC-12c(3c)/STM-4(1) ATM Optical Interface and 4-Port 1000Base-X Ethernet Optical Interface Line Card(WA)
hpnicfevtModuleSw-SR01CLP1GWA                 OBJECT IDENTIFIER ::= { hpnicfevtModuleSwitchType 329 } -- 1-Port OC-3/STM-1 CPOS Optical Interface and 4-Port 1000Base-X Ethernet Optical Interface Line Card(WA)
hpnicfevtModuleSw-SR01CLP2GWA                 OBJECT IDENTIFIER ::= { hpnicfevtModuleSwitchType 330 } -- 2-Port OC-3/STM-1 CPOS Optical Interface and 4-Port 1000Base-X Ethernet Optical Interface Line Card(WA)
hpnicfevtModuleSw-SR01ET16GWA                 OBJECT IDENTIFIER ::= { hpnicfevtModuleSwitchType 331 } -- 16-Port Channelized E1/T1 Interface and  4-Port 1000Base-X Ethernet Optical Interface Line Card(WA)
hpnicfevtModuleSw-SR01GP12VB                  OBJECT IDENTIFIER ::= { hpnicfevtModuleSwitchType 332 } -- 12-Port Gigabit Ethernet Optical Interface Card(VB)
hpnicfevtModuleSw-SR01XK1VB                   OBJECT IDENTIFIER ::= { hpnicfevtModuleSwitchType 333 } -- 1-Port 10Gigabit Ethernet Optical Interface Card(VB)
hpnicfevtModuleSw-SR01XP2VC                   OBJECT IDENTIFIER ::= { hpnicfevtModuleSwitchType 334 } -- 2-Port 10GBase-RW Ethernet XFP Optical Interface Line Card(VC)
hpnicfevtModuleSw-SR01XP4LVB                  OBJECT IDENTIFIER ::= { hpnicfevtModuleSwitchType 335 } -- 4-Port 10GBase-R/W Ethernet XFP Optical Interface Line Speed Card(VB)
hpnicfevtModuleSw-SR01SRPUEA                  OBJECT IDENTIFIER ::= { hpnicfevtModuleSwitchType 336 } -- Switching and Route Process Unit, Clock Module
hpnicfevtModuleSw-LSB1SRP1N4                  OBJECT IDENTIFIER ::= { hpnicfevtModuleSwitchType 337 } -- Switching and Route Process Unit, 12*LPU
hpnicfevtModuleSw-LSB1SRP1N5                  OBJECT IDENTIFIER ::= { hpnicfevtModuleSwitchType 338 } -- Switching and Route Process Unit, 8*LPU
hpnicfevtModuleSw-LSB1SRP1N6                  OBJECT IDENTIFIER ::= { hpnicfevtModuleSwitchType 339 } -- Switching and Route Process Unit, 5*LPU
hpnicfevtModuleSw-LSB1SRP1N7                  OBJECT IDENTIFIER ::= { hpnicfevtModuleSwitchType 340 } -- Switching and Route Process Unit, Clock Module
hpnicfevtModuleSw-LSB1SRP2N4                  OBJECT IDENTIFIER ::= { hpnicfevtModuleSwitchType 341 } -- Switching and Route Process Unit, 12*LPU
hpnicfevtModuleSw-LSB1SRP2N5                  OBJECT IDENTIFIER ::= { hpnicfevtModuleSwitchType 342 } -- Switching and Route Process Unit, 8*LPU
hpnicfevtModuleSw-LSB1SRP2N6                  OBJECT IDENTIFIER ::= { hpnicfevtModuleSwitchType 343 } -- Switching and Route Process Unit, 5*LPU
hpnicfevtModuleSw-LSB1SRP2N7                  OBJECT IDENTIFIER ::= { hpnicfevtModuleSwitchType 344 } -- Switching and Route Process Unit, Clock Module
hpnicfevtModuleSw-LSB1SRP1NA4                 OBJECT IDENTIFIER ::= { hpnicfevtModuleSwitchType 345 } -- Switching and Route Process Unit, 12*LPU
hpnicfevtModuleSw-LSB1SRP1NA5                 OBJECT IDENTIFIER ::= { hpnicfevtModuleSwitchType 346 } -- Switching and Route Process Unit, 8*LPU
hpnicfevtModuleSw-LSB1SRP1NA6                 OBJECT IDENTIFIER ::= { hpnicfevtModuleSwitchType 347 } -- Switching and Route Process Unit, 5*LPU
hpnicfevtModuleSw-LSB1SRP1NA7                 OBJECT IDENTIFIER ::= { hpnicfevtModuleSwitchType 348 } -- Switching and Route Process Unit, Clock Module
hpnicfevtModuleSw-LSB2GV48DA                  OBJECT IDENTIFIER ::= { hpnicfevtModuleSwitchType 349 } -- 48-Ports 1000Base-T Ethernet Interface Line Card with POE(DA)
hpnicfevtModuleSw-LSB1RGP2GDB                 OBJECT IDENTIFIER ::= { hpnicfevtModuleSwitchType 350 } -- 2-Port GE RPR and 8-Port GE Optical Interface Service Card(DB)
hpnicfevtModuleSw-LSB1RGP4GDB                 OBJECT IDENTIFIER ::= { hpnicfevtModuleSwitchType 351 } -- 4-Port GE RPR and 8-Port GE Optical Interface Service Card(DB)
hpnicfevtModuleSw-LSB2GP24DB                  OBJECT IDENTIFIER ::= { hpnicfevtModuleSwitchType 352 } -- 24-Port 1000BASE-X  Interface Module(DB),(SFP,LC)
hpnicfevtModuleSw-LSB2GP24DC                  OBJECT IDENTIFIER ::= { hpnicfevtModuleSwitchType 353 } -- 24-Port 1000BASE-X  Interface Module(DC),(SFP,LC)
hpnicfevtModuleSw-LSB2GT24DB                  OBJECT IDENTIFIER ::= { hpnicfevtModuleSwitchType 354 } -- 24-Port 10/100/1000BASE-T Interface Module(DB),(RJ45)
hpnicfevtModuleSw-LSB2FW8DB                   OBJECT IDENTIFIER ::= { hpnicfevtModuleSwitchType 355 } -- 8-Port 1000BASE-X Interface Firewall Service Module(DB),(SFP,LC)
hpnicfevtModuleSw-LSB2IPSEC8DB                OBJECT IDENTIFIER ::= { hpnicfevtModuleSwitchType 356 } -- 8-Port 1000BASE-X Interface IPSEC Service Module(DB),(SFP,LC)
hpnicfevtModuleSw-LSB2GV48DB                  OBJECT IDENTIFIER ::= { hpnicfevtModuleSwitchType 357 } -- 48-Port 10/100/1000BASE-T Interface Module(DB),(PoE,RJ45)
hpnicfevtModuleSw-RGP2                        OBJECT IDENTIFIER ::= { hpnicfevtModuleSwitchType 358 } -- 2-Port GE Resilient Packet Ring Interface Module
hpnicfevtModuleSw-RGP4                        OBJECT IDENTIFIER ::= { hpnicfevtModuleSwitchType 359 } -- 4-Port GE Resilient Packet Ring Interface Module
hpnicfevtModuleSw-SR02FW8VB                   OBJECT IDENTIFIER ::= { hpnicfevtModuleSwitchType 360 } -- 8-Port 1000BASE-X Interface Firewall Service Module(VB),(SFP,LC)
hpnicfevtModuleSw-SR02IPSEC8VB                OBJECT IDENTIFIER ::= { hpnicfevtModuleSwitchType 361 } -- 8-Port 1000BASE-X Interface IPSEC Service Module(VB),(SFP,LC)
hpnicfevtModuleSw-LSB2SRP1N0                  OBJECT IDENTIFIER ::= { hpnicfevtModuleSwitchType 362 } -- Switching and Route Process Unit, 12*LPU
hpnicfevtModuleSw-LSB2SRP1N1                  OBJECT IDENTIFIER ::= { hpnicfevtModuleSwitchType 363 } -- Switching and Route Process Unit, 8*LPU
hpnicfevtModuleSw-LSB2SRP1N2                  OBJECT IDENTIFIER ::= { hpnicfevtModuleSwitchType 364 } -- Switching and Route Process Unit, 5*LPU
hpnicfevtModuleSw-LSB2SRP1N3                  OBJECT IDENTIFIER ::= { hpnicfevtModuleSwitchType 365 } -- Switching and Route Process Unit, Clock module
hpnicfevtModuleSw-LSB2SRP1N4                  OBJECT IDENTIFIER ::= { hpnicfevtModuleSwitchType 366 } -- Switching and Route Process Unit, 12*LPU
hpnicfevtModuleSw-LSB2SRP1N5                  OBJECT IDENTIFIER ::= { hpnicfevtModuleSwitchType 367 } -- Switching and Route Process Unit, 8*LPU
hpnicfevtModuleSw-LSB2SRP1N6                  OBJECT IDENTIFIER ::= { hpnicfevtModuleSwitchType 368 } -- Switching and Route Process Unit, 5*LPU
hpnicfevtModuleSw-LSB2SRP1N7                  OBJECT IDENTIFIER ::= { hpnicfevtModuleSwitchType 369 } -- Switching and Route Process Unit, Clock module
hpnicfevtModuleSw-SR02SRPUE                   OBJECT IDENTIFIER ::= { hpnicfevtModuleSwitchType 370 } -- Switching and Route Process Unit, Clock module
hpnicfevtModuleSw-SR01LN1BQH0                 OBJECT IDENTIFIER ::= { hpnicfevtModuleSwitchType 371 } -- Single XG Service Board(BQH)
hpnicfevtModuleSw-SR01DXP1L                   OBJECT IDENTIFIER ::= { hpnicfevtModuleSwitchType 372 } -- 1-Port 10GBASE-R/W Ethernet Optical Interface Card,(XFP,LC)
hpnicfevtModuleSw-SR01DGP10L                  OBJECT IDENTIFIER ::= { hpnicfevtModuleSwitchType 373 } -- 10-Port 1000BASE-X Optical Interface Card,(SFP,LC)
hpnicfevtModuleSw-SR01DRSP2L                  OBJECT IDENTIFIER ::= { hpnicfevtModuleSwitchType 374 } -- 2-Port 2.5G RPR Optical Interface Card,(SFP,LC)
hpnicfevtModuleSw-SR01DRUP1L                  OBJECT IDENTIFIER ::= { hpnicfevtModuleSwitchType 375 } -- 1-Port 10G RPR Optical Interface Card,(XFP,LC)
hpnicfevtModuleSw-SR01DGP20R                  OBJECT IDENTIFIER ::= { hpnicfevtModuleSwitchType 376 } -- 20-Port 1000BASE-X Optical Interface Card,(SFP,LC)
hpnicfevtModuleSw-SR01DPLP8L                  OBJECT IDENTIFIER ::= { hpnicfevtModuleSwitchType 377 } -- 8-Port 155M POS Optical Interface Card,(SFP,LC)
hpnicfevtModuleSw-SR01DXP2R                   OBJECT IDENTIFIER ::= { hpnicfevtModuleSwitchType 378 } -- 2-Port 10GBASE-R/W Ethernet Optical Interface Card,(XFP,LC)
hpnicfevtModuleSw-LSB1FW2A0                   OBJECT IDENTIFIER ::= { hpnicfevtModuleSwitchType 379 } -- Gigabit Firewall Card, 4 Gigabit Port for Management
hpnicfevtModuleSw-LSB1GP48LDB                 OBJECT IDENTIFIER ::= { hpnicfevtModuleSwitchType 380 } -- 48-Port Line Rate Gigabit Ethernet Optical Interface Card(DB)
hpnicfevtModuleSw-SR01LN1BNA0                 OBJECT IDENTIFIER ::= { hpnicfevtModuleSwitchType 381 } -- Single XG Service Board(BNA)
hpnicfevtModuleSw-SR01LN2BQH0                 OBJECT IDENTIFIER ::= { hpnicfevtModuleSwitchType 382 } -- Dual XG Service Board(BQH)
hpnicfevtModuleSw-SR01LN2BNA0                 OBJECT IDENTIFIER ::= { hpnicfevtModuleSwitchType 383 } -- Dual XG Service Board(BNA)
hpnicfevtModuleSw-SR01DGT20R                  OBJECT IDENTIFIER ::= { hpnicfevtModuleSwitchType 384 } -- 20-Port 10/100/1000BASE-T Electrical Interface Card,(RJ45)
hpnicfevtModuleSw-SR01DPSP4L                  OBJECT IDENTIFIER ::= { hpnicfevtModuleSwitchType 385 } -- 4-Port 2.5G POS Optical Interface Card(SFP,LC)
hpnicfevtModuleSw-SR01DPUP1L                  OBJECT IDENTIFIER ::= { hpnicfevtModuleSwitchType 386 } -- 1-Port 10G POS Optical Interface Card,(XFP,LC)
hpnicfevtModuleSw-SR01DPL2G6L                 OBJECT IDENTIFIER ::= { hpnicfevtModuleSwitchType 387 } -- 2-Port 155M POS Optical Interface(SFP,LC)+6-Port 1000BASE-X Optical Interface Card(SFP,LC)
hpnicfevtModuleSw-SR01DPH2G6L                 OBJECT IDENTIFIER ::= { hpnicfevtModuleSwitchType 388 } -- 2-Port 622M POS Optical Interface(SFP,LC)+6-Port 1000BASE-X Optical Interface Card(SFP,LC)
hpnicfevtModuleSw-SR01DPS2G4L                 OBJECT IDENTIFIER ::= { hpnicfevtModuleSwitchType 389 } -- 2-Port 2.5G POS Optical Interface(SFP,LC)+4-Port 1000BASE-X Optical Interface Card(SFP,LC)
hpnicfevtModuleSw-SR01DCL1G8L                 OBJECT IDENTIFIER ::= { hpnicfevtModuleSwitchType 390 } -- 1-Port 155M CPOS Optical Interface(SFP,LC)+8-Port 1000BASE-X Optical Interface Card(SFP,LC)
hpnicfevtModuleSw-SR01DCL2G8L                 OBJECT IDENTIFIER ::= { hpnicfevtModuleSwitchType 391 } -- 2-Port 155M CPOS Optical Interface(SFP,LC)+8-Port 1000BASE-X Optical Interface Card(SFP,LC)
hpnicfevtModuleSw-SR01DET8G8L                 OBJECT IDENTIFIER ::= { hpnicfevtModuleSwitchType 392 } -- 8-Port E1/T1 Electrical Interface(RJ45)+8-Port 1000BASE-X Optical Interface Card(SFP,LC)
hpnicfevtModuleSw-SR02SRP2E3                  OBJECT IDENTIFIER ::= { hpnicfevtModuleSwitchType 393 } -- Switching and Route Process Unit, Clock module
hpnicfevtModuleSw-SR02SRP1E3                  OBJECT IDENTIFIER ::= { hpnicfevtModuleSwitchType 394 } -- Switching and Route Process Unit, Clock module
hpnicfevtModuleSw-SR02SRP1M3                  OBJECT IDENTIFIER ::= { hpnicfevtModuleSwitchType 395 } -- Switching and Route Process Unit, Clock module
hpnicfevtModuleSw-SR01DQCP4L                  OBJECT IDENTIFIER ::= { hpnicfevtModuleSwitchType 396 } -- 4-Port OC-3c/OC-12c/OC-48c POS/GE Optical Interface Card,(SFP,LC)
hpnicfevtModuleSw-SR01DTCP8L                  OBJECT IDENTIFIER ::= { hpnicfevtModuleSwitchType 397 } -- 8-Port OC-3c/OC-12c POS/GE Optical Interface Card,(SFP,LC)
hpnicfevtModuleSw-LSB1AFC1A0                  OBJECT IDENTIFIER ::= { hpnicfevtModuleSwitchType 398 } -- Anomaly Flow Cleaner Board
hpnicfevtModuleSw-LSB1SSL1A0                  OBJECT IDENTIFIER ::= { hpnicfevtModuleSwitchType 399 } -- SSL VPN High-end Board
hpnicfevtModuleSw-IMNAM                       OBJECT IDENTIFIER ::= { hpnicfevtModuleSwitchType 400 } -- Net Analysis Service Processing Board
hpnicfevtModuleSw-IMNAT                       OBJECT IDENTIFIER ::= { hpnicfevtModuleSwitchType 401 } -- Network Address Translation Service Processing Board
hpnicfevtModuleSw-PICAHP1L                    OBJECT IDENTIFIER ::= { hpnicfevtModuleSwitchType 402 } -- 1-Port OC-12c/STM-4c ATM Optical Interface Card,(SFP,LC)
hpnicfevtModuleSw-PICALP4L                    OBJECT IDENTIFIER ::= { hpnicfevtModuleSwitchType 403 } -- 4-Port OC-3c/STM-1c ATM Optical Interface Card,(SFP,LC)
hpnicfevtModuleSw-PICCHP4L                    OBJECT IDENTIFIER ::= { hpnicfevtModuleSwitchType 404 } -- 4-Port 622M CPOS Optical Interface Card(SFP,LC)
hpnicfevtModuleSw-PICCHS1G4L                  OBJECT IDENTIFIER ::= { hpnicfevtModuleSwitchType 405 } -- 1-Port 622M CPOS Optical Interface(Channelized to E3/T3)+4-Port 1000BASE-X Optical Interface Card(SFP,LC)
hpnicfevtModuleSw-PICCLS4G4L                  OBJECT IDENTIFIER ::= { hpnicfevtModuleSwitchType 406 } -- 4-Port 155M CPOS Optical Interface(Channelized to E3/T3)+4-Port 1000BASE-X Optical Interface Card(SFP,LC)
hpnicfevtModuleSw-PICCSP1L                    OBJECT IDENTIFIER ::= { hpnicfevtModuleSwitchType 407 } -- 1-Port 2.5G CPOS Optical Interface Card(SFP,LC)
hpnicfevtModuleSw-LSB1ACG1A0                  OBJECT IDENTIFIER ::= { hpnicfevtModuleSwitchType 408 } -- Application Control Gateway Board
hpnicfevtModuleSw-LST1MRPNC1                  OBJECT IDENTIFIER ::= { hpnicfevtModuleSwitchType 409 } -- Management and Route Process Unit
hpnicfevtModuleSw-LST1SF18B1                  OBJECT IDENTIFIER ::= { hpnicfevtModuleSwitchType 410 } -- S12518 Switch Fabric Card
hpnicfevtModuleSw-LST1SF08B1                  OBJECT IDENTIFIER ::= { hpnicfevtModuleSwitchType 411 } -- S12508 Switch Fabric Card
hpnicfevtModuleSw-LST1GT48LEC1                OBJECT IDENTIFIER ::= { hpnicfevtModuleSwitchType 412 } -- 48-Port 10/100/1000BASE-T Interface Module(LEC),(RJ45)
hpnicfevtModuleSw-LST1GP48LEC1                OBJECT IDENTIFIER ::= { hpnicfevtModuleSwitchType 413 } -- 48-Port 1000BASE-X Interface Module (LEC),(SFP,LC)
hpnicfevtModuleSw-LST1XP4LEC1                 OBJECT IDENTIFIER ::= { hpnicfevtModuleSwitchType 414 } -- 4-Port 10GBASE-R/W Interface Module (LEC),(XFP,LC)
hpnicfevtModuleSw-LST1XP8LEC1                 OBJECT IDENTIFIER ::= { hpnicfevtModuleSwitchType 415 } -- 8-Port 10GBASE-R/W Interface Module (LEC),(XFP,LC)
hpnicfevtModuleSw-LSR1SRP2B1                  OBJECT IDENTIFIER ::= { hpnicfevtModuleSwitchType 416 } -- Switching and Route Process Unit
hpnicfevtModuleSw-LSR1SRP2C1                  OBJECT IDENTIFIER ::= { hpnicfevtModuleSwitchType 417 } -- Switching and Route Process Unit
hpnicfevtModuleSw-LSR1SRP2B2                  OBJECT IDENTIFIER ::= { hpnicfevtModuleSwitchType 418 } -- Switching and Route Process Unit
hpnicfevtModuleSw-LSR1SRP2C2                  OBJECT IDENTIFIER ::= { hpnicfevtModuleSwitchType 419 } -- Switching and Route Process Unit
hpnicfevtModuleSw-LSR1GT24LEC1                OBJECT IDENTIFIER ::= { hpnicfevtModuleSwitchType 420 } -- 16-Port 10/100/1000BASE-T Interface and 8-port 1000BASE-T/1000BASE-X Combo Interface Service Card(LEC)
hpnicfevtModuleSw-LSR1GP24LEB1                OBJECT IDENTIFIER ::= { hpnicfevtModuleSwitchType 421 } -- 16-Port 1000BASE-X Interface and 8-port 1000BASE-T/1000BASE-X Combo Interface Service Card(LEB)
hpnicfevtModuleSw-LSR1GP24LEC1                OBJECT IDENTIFIER ::= { hpnicfevtModuleSwitchType 422 } -- 16-Port 1000BASE-X Interface and 8-port 1000BASE-T/1000BASE-X Combo Interface Service Card(LEC)
hpnicfevtModuleSw-LSR1GT48LEB1                OBJECT IDENTIFIER ::= { hpnicfevtModuleSwitchType 423 } -- 48-Port 10/100/1000BASE-T Interface Module(LEB),(RJ45)
hpnicfevtModuleSw-LSR1GT48LEC1                OBJECT IDENTIFIER ::= { hpnicfevtModuleSwitchType 424 } -- 48-Port 10/100/1000BASE-T Interface Module(LEC),(RJ45)
hpnicfevtModuleSw-LSR1GP48LEB1                OBJECT IDENTIFIER ::= { hpnicfevtModuleSwitchType 425 } -- 48-Port 1000BASE-X Interface Module(LEB),(SFP,LC)
hpnicfevtModuleSw-LSR1GP48LEC1                OBJECT IDENTIFIER ::= { hpnicfevtModuleSwitchType 426 } -- 48-Port 1000BASE-X Interface Module(LEC),(SFP,LC)
hpnicfevtModuleSw-LSR2GV48REB1                OBJECT IDENTIFIER ::= { hpnicfevtModuleSwitchType 427 } -- 48-Port 10/100/1000BASE-T Interface Module(REB),(PoE,RJ45)
hpnicfevtModuleSw-LSR1XP2LEB1                 OBJECT IDENTIFIER ::= { hpnicfevtModuleSwitchType 428 } -- 2-Port 10GBase-R/W Interface Module (LEB),(XFP,LC)
hpnicfevtModuleSw-LSR1XP2LEC1                 OBJECT IDENTIFIER ::= { hpnicfevtModuleSwitchType 429 } -- 2-Port 10GBase-R/W Interface Module (LEC),(XFP,LC)
hpnicfevtModuleSw-LSR1XP4LEB1                 OBJECT IDENTIFIER ::= { hpnicfevtModuleSwitchType 430 } -- 4-Port 10GBase-R/W Interface Module (LEB),(XFP,LC)
hpnicfevtModuleSw-LSR1XP4LEC1                 OBJECT IDENTIFIER ::= { hpnicfevtModuleSwitchType 431 } -- 4-Port 10GBase-R/W Interface Module (LEC),(XFP,LC)
hpnicfevtModuleSw-IMFW                        OBJECT IDENTIFIER ::= { hpnicfevtModuleSwitchType 432 } -- Firewall Service Processing Board
hpnicfevtModuleSw-LSB1LB1A0                   OBJECT IDENTIFIER ::= { hpnicfevtModuleSwitchType 433 } -- Load Balance Board
hpnicfevtModuleSw-LSB1IPS1A0                  OBJECT IDENTIFIER ::= { hpnicfevtModuleSwitchType 434 } -- Gigabit IPS Card
hpnicfevtModuleSw-LST1GT48LEB1                OBJECT IDENTIFIER ::= { hpnicfevtModuleSwitchType 435 } -- 48-Port 10/100/1000BASE-T Interface Module(LEB),(RJ45)
hpnicfevtModuleSw-LST1GP48LEB1                OBJECT IDENTIFIER ::= { hpnicfevtModuleSwitchType 436 } -- 48-Port 1000BASE-X Interface Module (LEB),(SFP,LC)
hpnicfevtModuleSw-LST1XP4LEB1                 OBJECT IDENTIFIER ::= { hpnicfevtModuleSwitchType 437 } -- 4-Port 10GBASE-R/W Interface Module (LEB),(XFP,LC)
hpnicfevtModuleSw-LST1XP8LEB1                 OBJECT IDENTIFIER ::= { hpnicfevtModuleSwitchType 438 } -- 8-Port 10GBASE-R/W Interface Module (LEB),(XFP,LC)
hpnicfevtModuleSw-LST1XP32REB1                OBJECT IDENTIFIER ::= { hpnicfevtModuleSwitchType 439 } -- 32-Port 10GBASE-R Interface Module (REB),(SFP+,LC)
hpnicfevtModuleSw-LST1XP32REC1                OBJECT IDENTIFIER ::= { hpnicfevtModuleSwitchType 440 } -- 32-Port 10GBASE-R Interface Module (REC),(SFP+,LC)
hpnicfevtModuleSw-LSR1FW2A1                   OBJECT IDENTIFIER ::= { hpnicfevtModuleSwitchType 441 } -- Firewall Service Module
hpnicfevtModuleSw-LSR1SSL1A1                  OBJECT IDENTIFIER ::= { hpnicfevtModuleSwitchType 442 } -- SSL VPN Service Module
hpnicfevtModuleSw-SR01DET32G2L                OBJECT IDENTIFIER ::= { hpnicfevtModuleSwitchType 443 } -- 32-Port E1/T1 75ohm Electrical Interface(DB56 Female Socket)+2-Port 1000BASE-X Optical Interface Card(SFP,LC)
hpnicfevtModuleSw-LSR1GP24LEF1                OBJECT IDENTIFIER ::= { hpnicfevtModuleSwitchType 444 } -- 16-Port 1000BASE-X Interface and 8-port 1000BASE-T/1000BASE-X Combo Interface Service Card(LEF)
hpnicfevtModuleSw-LSR1XP4LEF1                 OBJECT IDENTIFIER ::= { hpnicfevtModuleSwitchType 445 } -- 4-Port 10GBASE-R/W Interface Module (LEF),(XFP,LC)
hpnicfevtModuleSw-LSR1LB1A1                   OBJECT IDENTIFIER ::= { hpnicfevtModuleSwitchType 446 } -- Load Balance Module
hpnicfevtModuleSw-LSR1NSM1A1                  OBJECT IDENTIFIER ::= { hpnicfevtModuleSwitchType 447 } -- NetStream Module
hpnicfevtModuleSw-LSR1ACG1A1                  OBJECT IDENTIFIER ::= { hpnicfevtModuleSwitchType 448 } -- Application Control Gateway Service Module
hpnicfevtModuleSw-LSR1IPS1A1                  OBJECT IDENTIFIER ::= { hpnicfevtModuleSwitchType 449 } -- Intrusion Protection System Service Module
hpnicfevtModuleSw-LSR2GP24LEB1                OBJECT IDENTIFIER ::= { hpnicfevtModuleSwitchType 450 } -- 16-Port 1000BASE-X Interface and 8-port 1000BASE-T/1000BASE-X Combo Interface Service Card(LEB)
hpnicfevtModuleSw-LSR2GT24LEB1                OBJECT IDENTIFIER ::= { hpnicfevtModuleSwitchType 451 } -- 16-Port 10/100/1000BASE-T Interface and 8-port 1000BASE-T/1000BASE-X Combo Interface Service Card(LEB)
hpnicfevtModuleSw-LSR2GT48LEB1                OBJECT IDENTIFIER ::= { hpnicfevtModuleSwitchType 452 } -- 48-Port 10/100/1000BASE-T Interface Module(LEB),(RJ45)
hpnicfevtModuleSw-SPC-GP24L                   OBJECT IDENTIFIER ::= { hpnicfevtModuleSwitchType 453 } -- 24-Port 1000BASE-X Interface Service Card,(SFP,LC)
hpnicfevtModuleSw-SPC-GT48L                   OBJECT IDENTIFIER ::= { hpnicfevtModuleSwitchType 454 } -- 48-Port 10/100/1000BASE-T Interface Module,(RJ45)
hpnicfevtModuleSw-SPC-GP48L                   OBJECT IDENTIFIER ::= { hpnicfevtModuleSwitchType 455 } -- 48-Port 1000BASE-X Interface Module,(SFP,LC)
hpnicfevtModuleSw-SPC-XP2L                    OBJECT IDENTIFIER ::= { hpnicfevtModuleSwitchType 456 } -- 2-Port 10GBASE-R/W Interface Service Card,(XFP,LC)
hpnicfevtModuleSw-SPC-XP4L                    OBJECT IDENTIFIER ::= { hpnicfevtModuleSwitchType 457 } -- 4-Port 10GBase-R/W Interface Module,(XFP,LC)
hpnicfevtModuleSw-SR06SRP2E3                  OBJECT IDENTIFIER ::= { hpnicfevtModuleSwitchType 458 } -- SDI,Routing Switch Processing Board
hpnicfevtModuleSw-SPE-2010-E                  OBJECT IDENTIFIER ::= { hpnicfevtModuleSwitchType 459 } -- SDI,Single XG Service Board
hpnicfevtModuleSw-SPE-2020-E                  OBJECT IDENTIFIER ::= { hpnicfevtModuleSwitchType 460 } -- SDI,Dual XG Service Board
hpnicfevtModuleSw-SPC-XP4L-S-SDI              OBJECT IDENTIFIER ::= { hpnicfevtModuleSwitchType 461 } -- SDI 4-Port 10GBase-R/W Interface Module,(XFP,LC)
hpnicfevtModuleSw-SPC-GT48L-SDI               OBJECT IDENTIFIER ::= { hpnicfevtModuleSwitchType 462 } -- SDI 48-Port 10/100/1000BASE-T Interface Module,(RJ45)
hpnicfevtModuleSw-SPC-GP48L-S-SDI             OBJECT IDENTIFIER ::= { hpnicfevtModuleSwitchType 463 } -- SDI 48-Port 1000BASE-X Interface Module,(SFP,LC)
hpnicfevtModuleSw-SPC-SR02OPMA0               OBJECT IDENTIFIER ::= { hpnicfevtModuleSwitchType 464 } -- Single Mode 1310&1550nm Optical Protect Board(LC)
hpnicfevtModuleSw-LSR1XP16REB1                OBJECT IDENTIFIER ::= { hpnicfevtModuleSwitchType 465 } -- 16-Port 10GBASE-R Interface Module (REB),(SFP+,LC)
hpnicfevtModuleSw-LSR1GP48LEF1                OBJECT IDENTIFIER ::= { hpnicfevtModuleSwitchType 466 } -- 48-Port 1000BASE-X Interface Module (LEF),(SFP,LC)
hpnicfevtModuleSw-LST1GP48LEF1                OBJECT IDENTIFIER ::= { hpnicfevtModuleSwitchType 467 } -- 48-Port 1000BASE-X Interface Module (LEF),(SFP,LC)
hpnicfevtModuleSw-LST1XP8LEF1                 OBJECT IDENTIFIER ::= { hpnicfevtModuleSwitchType 468 } -- 8-Port 10GBASE-R/W Interface Module (LEF),(XFP,LC)
hpnicfevtModuleSw-SPE-1010-II                 OBJECT IDENTIFIER ::= { hpnicfevtModuleSwitchType 469 } -- Single XG Service Board-II
hpnicfevtModuleSw-SPE-1010-E-II               OBJECT IDENTIFIER ::= { hpnicfevtModuleSwitchType 470 } -- Enhanced Single XG Service Board-II
hpnicfevtModuleSw-SPE-1020-II                 OBJECT IDENTIFIER ::= { hpnicfevtModuleSwitchType 471 } -- Double XG Service Board-II
hpnicfevtModuleSw-SPE-1020-E-II               OBJECT IDENTIFIER ::= { hpnicfevtModuleSwitchType 472 } -- Enhanced Double XG Service Board-II
hpnicfevtModuleSw-LST1FW2A1                   OBJECT IDENTIFIER ::= { hpnicfevtModuleSwitchType 473 } -- Firewall Board (LEC)
hpnicfevtModuleSw-LST1NSM1A1                  OBJECT IDENTIFIER ::= { hpnicfevtModuleSwitchType 474 } -- NetStream Service Board (LEC)
hpnicfevtModuleSw-LST1LB1A1                   OBJECT IDENTIFIER ::= { hpnicfevtModuleSwitchType 475 } -- Load Balancing Board (LEC)
hpnicfevtModuleSw-LST1ACG1A1                  OBJECT IDENTIFIER ::= { hpnicfevtModuleSwitchType 476 } -- Application Control Gateway Board Module (LEC)
hpnicfevtModuleSw-LST1IPS1A1                  OBJECT IDENTIFIER ::= { hpnicfevtModuleSwitchType 477 } -- Gigabit Intrusion Prevention System Module (LEC)
hpnicfevtModuleSw-LSR1DRUP1L1                 OBJECT IDENTIFIER ::= { hpnicfevtModuleSwitchType 478 } -- 1-Port OC-192c/STM-64c RPR Optical Interface Card,(XFP,LC)
hpnicfevtModuleSw-LSR1DPUP1L1                 OBJECT IDENTIFIER ::= { hpnicfevtModuleSwitchType 479 } -- 1-Port OC-192c/STM-64c POS Optical Interface Card,(XFP,LC)
hpnicfevtModuleSw-LSR1DPSP4L1                 OBJECT IDENTIFIER ::= { hpnicfevtModuleSwitchType 480 } -- 4-Port OC-48c/STM-16c POS Optical Interface Card,(SFP,LC)
hpnicfevtModuleSw-LSR1DTCP8L1                 OBJECT IDENTIFIER ::= { hpnicfevtModuleSwitchType 481 } -- 8-Port OC-3c/OC-12c POS/GE Optical Interface Card,(SFP,LC)
hpnicfevtModuleSw-LSR1DXP1L1                  OBJECT IDENTIFIER ::= { hpnicfevtModuleSwitchType 482 } -- 1-Port 10GBASE-R/W Ethernet Optical Interface Card,(XPF,LC)
hpnicfevtModuleSw-LSR1DGP10L1                 OBJECT IDENTIFIER ::= { hpnicfevtModuleSwitchType 483 } -- 10-Port 1000BASE-X Optical Interface Card,(SFP,LC)
hpnicfevtModuleSw-LSR1LN1BNL1                 OBJECT IDENTIFIER ::= { hpnicfevtModuleSwitchType 484 } -- Single Service Processing Board
hpnicfevtModuleSw-LSR1LN2BL1                  OBJECT IDENTIFIER ::= { hpnicfevtModuleSwitchType 485 } -- Dual Serivice Processing Board
hpnicfevtModuleSw-LSR1SRP2D1                  OBJECT IDENTIFIER ::= { hpnicfevtModuleSwitchType 486 } -- Switching and Route Process Unit With Clock
hpnicfevtModuleSw-IM-NAT-II                   OBJECT IDENTIFIER ::= { hpnicfevtModuleSwitchType 487 } -- Network Address Translation Service Processing Board,II
hpnicfevtModuleSw-IM-NAM-II                   OBJECT IDENTIFIER ::= { hpnicfevtModuleSwitchType 488 } -- Net Analysis Service Processing Board,II
hpnicfevtModuleSw-CR-MRP-I                    OBJECT IDENTIFIER ::= { hpnicfevtModuleSwitchType 489 } -- Management and Route Unit With OAM Module and Clock Module
hpnicfevtModuleSw-CR-SF18C                    OBJECT IDENTIFIER ::= { hpnicfevtModuleSwitchType 490 } -- Switch Fabric Card
hpnicfevtModuleSw-CR-SF08C                    OBJECT IDENTIFIER ::= { hpnicfevtModuleSwitchType 491 } -- Switch Fabric Card
hpnicfevtModuleSw-CR-SPC-XP8LEF               OBJECT IDENTIFIER ::= { hpnicfevtModuleSwitchType 492 } -- 8-Port 10GBASE-R/W Interface Module,(XFP,LC)
hpnicfevtModuleSw-CR-SPC-XP4LEF               OBJECT IDENTIFIER ::= { hpnicfevtModuleSwitchType 493 } -- 4-Port 10GBASE-R/W Interface Module,(XFP,LC)
hpnicfevtModuleSw-CR-SPC-GP48LEF              OBJECT IDENTIFIER ::= { hpnicfevtModuleSwitchType 494 } -- 48-Port 1000BASE-X Interface Module,(SFP,LC)
hpnicfevtModuleSw-CR-SPC-GT48LEF              OBJECT IDENTIFIER ::= { hpnicfevtModuleSwitchType 495 } -- 48-Port 10/100/1000BASE-T Interface Module
hpnicfevtModuleSw-CR-SPE-3020-E               OBJECT IDENTIFIER ::= { hpnicfevtModuleSwitchType 496 } -- Double XG Service Board (Enhanced)
hpnicfevtModuleSw-CR-SPC-PUP4L-E              OBJECT IDENTIFIER ::= { hpnicfevtModuleSwitchType 497 } -- 4-Port 10G POS Optical Interface Module,(XFP,LC)
hpnicfevtModuleSw-LST1SF08C1                  OBJECT IDENTIFIER ::= { hpnicfevtModuleSwitchType 498 } -- Switch Fabric Card
hpnicfevtModuleSw-LST1SF18C1                  OBJECT IDENTIFIER ::= { hpnicfevtModuleSwitchType 499 } -- Switch Fabric Card

--
-- 500 to 699 reserved for secondary switches part I
--
hpnicfevtModuleSw-LS81GP16TM                  OBJECT IDENTIFIER ::= { hpnicfevtModuleSwitchType 500 } -- 12-port 1000BASE-X SFP Interface and 4-port 1000BASE-T/1000BASE-X Combo Interface Metro Switch and Route Processing Board
hpnicfevtModuleSw-LS81VP4C                    OBJECT IDENTIFIER ::= { hpnicfevtModuleSwitchType 501 } -- 4-port 1000BASE-X SFP Interface Virtual Daughter Card
hpnicfevtModuleSw-LS8M1PT8P0                  OBJECT IDENTIFIER ::= { hpnicfevtModuleSwitchType 502 } -- 8-Port 1000BASE-PX Optical Line Interface Board, SFP Req
hpnicfevtModuleSw-LS8M1PT8GB0                 OBJECT IDENTIFIER ::= { hpnicfevtModuleSwitchType 503 } -- 8-Port 1000BASE-PX20 Gigabit Passive Optical Line Interface Board B(20km, SFF), SC Connector
hpnicfevtModuleSw-LS8M1PT4GB0                 OBJECT IDENTIFIER ::= { hpnicfevtModuleSwitchType 504 } -- 4-Port 1000BASE-PX20 Gigabit Passive Optical Line Interface Board B(20km, SFF), SC Connector
hpnicfevtModuleSw-LS81GP2R                    OBJECT IDENTIFIER ::= { hpnicfevtModuleSwitchType 505 } -- 2-port 1000M Ethernet Optical Interface RPR Board
hpnicfevtModuleSw-LS81GP4R                    OBJECT IDENTIFIER ::= { hpnicfevtModuleSwitchType 506 } -- 4-port 1000M Ethernet Optical Interface RPR Board
hpnicfevtModuleSw-LS81IPSECA                  OBJECT IDENTIFIER ::= { hpnicfevtModuleSwitchType 507 } -- IPSec Service Board
hpnicfevtModuleSw-LS81FWA                     OBJECT IDENTIFIER ::= { hpnicfevtModuleSwitchType 508 } -- Firewall Service Board
hpnicfevtModuleSw-LS82VSNP                    OBJECT IDENTIFIER ::= { hpnicfevtModuleSwitchType 509 } -- Versatile Network Processing Service Module (PBR/NAT/NetStream) with 12-port 1000BASE-X SFP, XGBUS Uplink
hpnicfevtModuleSw-LSQ1GV48SA                  OBJECT IDENTIFIER ::= { hpnicfevtModuleSwitchType 510 } -- 48-Port 1000Base-T Gigabit Ethernet Interface Board(RJ45)
hpnicfevtModuleSw-LSQ1SRPB                    OBJECT IDENTIFIER ::= { hpnicfevtModuleSwitchType 511 } -- Salience VI
hpnicfevtModuleSw-LSQ1SRP2XB                  OBJECT IDENTIFIER ::= { hpnicfevtModuleSwitchType 512 } -- Salience VI-10GE
hpnicfevtModuleSw-LSQ1SRP1CB                  OBJECT IDENTIFIER ::= { hpnicfevtModuleSwitchType 513 } -- Salience VI-Turbo
hpnicfevtModuleSw-LSQ1FV48SA                  OBJECT IDENTIFIER ::= { hpnicfevtModuleSwitchType 514 } -- 48-Port 100M Ethernet Electrical Interface Switch Unit(RJ45)
hpnicfevtModuleSw-LSD1MPUA                    OBJECT IDENTIFIER ::= { hpnicfevtModuleSwitchType 515 } -- Main Control Unit
hpnicfevtModuleSw-LSD1GP20A0                  OBJECT IDENTIFIER ::= { hpnicfevtModuleSwitchType 516 } -- 16-port 1000BASE-X SFP Interface and 4-port 1000BASE-T/1000BASE-X Combo Interface Line Card
hpnicfevtModuleSw-LSD1GP20TA0                 OBJECT IDENTIFIER ::= { hpnicfevtModuleSwitchType 517 } -- 16-port 1000BASE-X SFP Interface and 4-port 1000BASE-T/1000BASE-X Combo Interface and 16 1000BASE-T Interface Line Card
hpnicfevtModuleSw-LSD1GP36A0                  OBJECT IDENTIFIER ::= { hpnicfevtModuleSwitchType 518 } -- 32-port 1000BASE-X SFP Interface and 4-port 1000BASE-T/1000BASE-X Combo Interface Line Card
hpnicfevtModuleSw-LSD1GP20XA0                 OBJECT IDENTIFIER ::= { hpnicfevtModuleSwitchType 519 } -- 16-port 1000BASE-X SFP Interface and 4-port 1000BASE-T/1000BASE-X Combo Interface and 2-port 10GBASE-X XFP Interface Line Card
hpnicfevtModuleSw-LSD1GP20EA0                 OBJECT IDENTIFIER ::= { hpnicfevtModuleSwitchType 520 } -- 16-port 1000BASE-X SFP Interface and 4-port 1000BASE-T/1000BASE-X Combo Interface and 2-port GE RPR Interface Line Card
hpnicfevtModuleSw-LSD1GP20RA0                 OBJECT IDENTIFIER ::= { hpnicfevtModuleSwitchType 521 } -- 16-port 1000BASE-X SFP Interface and 4-port 1000BASE-T/1000BASE-X Combo Interface and 2-port OC48 RPR Interface Line Card
hpnicfevtModuleSw-LSD1GP16A0                  OBJECT IDENTIFIER ::= { hpnicfevtModuleSwitchType 522 } -- 16-port 1000BASE-X SFP Ethernet Interface SubCard
hpnicfevtModuleSw-LSD1GT16A0                  OBJECT IDENTIFIER ::= { hpnicfevtModuleSwitchType 523 } -- 16-port 1000BASE-T Ethernet Interface SubCard
hpnicfevtModuleSw-LSD1XP2A0                   OBJECT IDENTIFIER ::= { hpnicfevtModuleSwitchType 524 } -- 2-port 10GBASE-X XFP Ethernet Interface SubCard
hpnicfevtModuleSw-LSD1EP2A0                   OBJECT IDENTIFIER ::= { hpnicfevtModuleSwitchType 525 } -- 2-port 1000BASE-T Ethernet RPR Interface SubCard
hpnicfevtModuleSw-LSD1RP2A0                   OBJECT IDENTIFIER ::= { hpnicfevtModuleSwitchType 526 } -- 2-port OC48 RPR Interface SubCard
hpnicfevtModuleSw-LSQ1GV48SC                  OBJECT IDENTIFIER ::= { hpnicfevtModuleSwitchType 527 } -- 48-Port 1000Base-T Gigabit Ethernet Interface Board(RJ45)-POE
hpnicfevtModuleSw-LSQ1FP48SA                  OBJECT IDENTIFIER ::= { hpnicfevtModuleSwitchType 528 } -- 48 Port 100M Ethernet Optical Interface Board(SFP,LC)
hpnicfevtModuleSw-LSQ1GP24SC                  OBJECT IDENTIFIER ::= { hpnicfevtModuleSwitchType 529 } -- 24 Port 1000BASE-X Ethernet Optical Interface Board(SFP,LC)
hpnicfevtModuleSw-LSQ1GT24SC                  OBJECT IDENTIFIER ::= { hpnicfevtModuleSwitchType 530 } -- 24-Port 1000BASE-T Ethernet Interface Board (RJ45)
hpnicfevtModuleSw-LSQ1TGX2SC                  OBJECT IDENTIFIER ::= { hpnicfevtModuleSwitchType 531 } -- 2-Port 10GBASE Ethernet Optical Interface Board(XFP,LC)
hpnicfevtModuleSw-LSQ1GP12EA                  OBJECT IDENTIFIER ::= { hpnicfevtModuleSwitchType 532 } -- 12-Port 1000BASE-X Ethernet Optical Interface Board(SFP,LC)
hpnicfevtModuleSw-LSQ1TGX1EA                  OBJECT IDENTIFIER ::= { hpnicfevtModuleSwitchType 533 } -- 1-Port 10GBASE Ethernet Optical Interface Module(XFP,LC)
hpnicfevtModuleSw-LSQ1P24XGSC                 OBJECT IDENTIFIER ::= { hpnicfevtModuleSwitchType 534 } -- 24-Port 1000BASE-X Gigabit Ethernet Optical Interface(SFP,LC)+2-Port 10GBASE Ethernet Optical Interface Board(XFP,LC)
hpnicfevtModuleSw-LSQ1T24XGSC                 OBJECT IDENTIFIER ::= { hpnicfevtModuleSwitchType 535 } -- 24-Port 1000BASE-T Gigabit Ethernet Interface(RJ45)+2-Port 10GBASE Ethernet Optical Interface Board(XFP,LC)
hpnicfevtModuleSw-LS81TGX1B                   OBJECT IDENTIFIER ::= { hpnicfevtModuleSwitchType 536 } -- 1 Port 10GBase-R Ethernet Interface Board(XENPAK,SC)
hpnicfevtModuleSw-LSQ1PT4PSC0                 OBJECT IDENTIFIER ::= { hpnicfevtModuleSwitchType 537 } -- 4-Port 1000Base-PX Optical Line Terminal(EPON OLT SFP,SC)+8-Port 1000BASE-X Optical Interface Board(SFP,LC)
hpnicfevtModuleSw-LS81SRPG13                  OBJECT IDENTIFIER ::= { hpnicfevtModuleSwitchType 538 } -- Salience V, Switch and Route Processing Board
hpnicfevtModuleSw-LS81SRPG14                  OBJECT IDENTIFIER ::= { hpnicfevtModuleSwitchType 539 } -- Salience V Edge
hpnicfevtModuleSw-LS81SRPG15                  OBJECT IDENTIFIER ::= { hpnicfevtModuleSwitchType 540 } -- Salience V Plus
hpnicfevtModuleSw-LSQ1GP48SC0                 OBJECT IDENTIFIER ::= { hpnicfevtModuleSwitchType 541 } -- 48-Port 1000BASE Ethernet Optical Interface Board(SFP,LC)
hpnicfevtModuleSw-LSQ1GP12SC0                 OBJECT IDENTIFIER ::= { hpnicfevtModuleSwitchType 542 } -- 12-Port 1000BASE-X Ethernet Optical Interface Board(SFP,LC)
hpnicfevtModuleSw-LSD1SRPA                    OBJECT IDENTIFIER ::= { hpnicfevtModuleSwitchType 543 } -- Salience VIII 160
hpnicfevtModuleSw-LSD1SRPB                    OBJECT IDENTIFIER ::= { hpnicfevtModuleSwitchType 544 } -- Salience VIII 480
hpnicfevtModuleSw-LSD1SRPC                    OBJECT IDENTIFIER ::= { hpnicfevtModuleSwitchType 545 } -- Salience VIII 800
hpnicfevtModuleSw-LSD1GT16PES0                OBJECT IDENTIFIER ::= { hpnicfevtModuleSwitchType 546 } -- 16-Port 10/100/1000BASE-T and 8-Port 100/1000BASE-X SFP Interface Card
hpnicfevtModuleSw-LSD1GP24ES0                 OBJECT IDENTIFIER ::= { hpnicfevtModuleSwitchType 547 } -- 24-Port 1000BASE-X Ethernet SFP Interface Card
hpnicfevtModuleSw-LSD1GT24XES0                OBJECT IDENTIFIER ::= { hpnicfevtModuleSwitchType 548 } -- 24-Port 10/100/1000BASE-T and 2-port 10GBASE-X Ethernet XFP Optical Interface Card
hpnicfevtModuleSw-LSD1GP24XES0                OBJECT IDENTIFIER ::= { hpnicfevtModuleSwitchType 549 } -- 24-Port 1000BASE-X Ethernet SFP interface and 2-port 10GBASE-X Ethernet XFP Optical Interface Card
hpnicfevtModuleSw-LSD1XP2ES0                  OBJECT IDENTIFIER ::= { hpnicfevtModuleSwitchType 550 } -- 2-Port 10GBASE-X Ethernet XFP Optical Interface Card
hpnicfevtModuleSw-LSD1GP48ES0                 OBJECT IDENTIFIER ::= { hpnicfevtModuleSwitchType 551 } -- 48-Port 1000BASE-X Ethernet SFP Interface Card
hpnicfevtModuleSw-LSQ1MPUA0                   OBJECT IDENTIFIER ::= { hpnicfevtModuleSwitchType 552 } -- Master Process Board
hpnicfevtModuleSw-LSQ1MPUA1                   OBJECT IDENTIFIER ::= { hpnicfevtModuleSwitchType 553 } -- Master Process Unit
hpnicfevtModuleSw-LSQ1FWBSC0                  OBJECT IDENTIFIER ::= { hpnicfevtModuleSwitchType 554 } -- Gigabit Firewall Card,4 Gigabit Port for Management
hpnicfevtModuleSw-LSQ1PT8PSC0                 OBJECT IDENTIFIER ::= { hpnicfevtModuleSwitchType 555 } -- 8-Port 1000Base-PX Optical Line Terminal(EPON OLT SFP,SC)+8-Port 1000BASE-X Optical Interface Board(SFP,LC)
hpnicfevtModuleSw-LSQ1PT16PSC0                OBJECT IDENTIFIER ::= { hpnicfevtModuleSwitchType 556 } -- 16-Port 1000Base-PX Optical Line Terminal(EPON OLT SFP,SC)+8-Port 1000BASE-X Optical Interface Board(SFP,LC)
hpnicfevtModuleSw-SA11MPUA0                   OBJECT IDENTIFIER ::= { hpnicfevtModuleSwitchType 557 } -- SmartEngine I-Lite
hpnicfevtModuleSw-SA11MPUB0                   OBJECT IDENTIFIER ::= { hpnicfevtModuleSwitchType 558 } -- SmartEngine I
hpnicfevtModuleSw-LSQ1AFCBSC0                 OBJECT IDENTIFIER ::= { hpnicfevtModuleSwitchType 559 } -- Anomaly Flow Cleaner Board Interface Board(SFP,LC)
hpnicfevtModuleSw-LSQ1MPUB0                   OBJECT IDENTIFIER ::= { hpnicfevtModuleSwitchType 560 } -- Salience VI-Lite
hpnicfevtModuleSw-LSQ1MPUB1                   OBJECT IDENTIFIER ::= { hpnicfevtModuleSwitchType 561 } -- Salience VI-Lite
hpnicfevtModuleSw-LSQ1PT4PSC1                 OBJECT IDENTIFIER ::= { hpnicfevtModuleSwitchType 562 } -- 4-Port 1000Base-PX Optical Line Terminal(EPON OLT SFP,SC)+8-Port 1000BASE-X Optical Interface Board(SFP,LC)
hpnicfevtModuleSw-LSQ1PT8PSC1                 OBJECT IDENTIFIER ::= { hpnicfevtModuleSwitchType 563 } -- 8-Port 1000Base-PX Optical Line Terminal(EPON OLT SFP,SC)+8-Port 1000BASE-X Optical Interface Board(SFP,LC)
hpnicfevtModuleSw-LSQ1PT16PSC1                OBJECT IDENTIFIER ::= { hpnicfevtModuleSwitchType 564 } -- 16-Port 1000Base-PX Optical Line Terminal(EPON OLT SFP,SC)+8-Port 1000BASE-X Optical Interface Board(SFP,LC)
hpnicfevtModuleSw-LSQ1FP48USA0                OBJECT IDENTIFIER ::= { hpnicfevtModuleSwitchType 565 } -- 48-Port 100M Ethernet Optical Interface Switch Unit(SFP,LC)
hpnicfevtModuleSw-LSQ1FP48USA1                OBJECT IDENTIFIER ::= { hpnicfevtModuleSwitchType 566 } -- 48-Port 100M Ethernet Optical Interface Switch Unit(SFP,LC)
hpnicfevtModuleSw-LSQ1FV48USA0                OBJECT IDENTIFIER ::= { hpnicfevtModuleSwitchType 567 } -- 48-Port 100M Ethernet Electrical Interface Switch Unit(RJ45),PoE
hpnicfevtModuleSw-LSQ1FV48USA1                OBJECT IDENTIFIER ::= { hpnicfevtModuleSwitchType 568 } -- 48-Port 100M Ethernet Electrical Interface Switch Unit(RJ45),PoE
hpnicfevtModuleSw-LSQ1SRPD0                   OBJECT IDENTIFIER ::= { hpnicfevtModuleSwitchType 569 } -- Switch and Route Processing Unit, Salience VI-Plus
hpnicfevtModuleSw-LSQ1CGP24TSC0               OBJECT IDENTIFIER ::= { hpnicfevtModuleSwitchType 570 } -- Switching and Routing Processing Unit with 24 1000BASE-X Gigabit Ethernet Optical Ports,including 8 Combo Ports,SFP Req.
hpnicfevtModuleSw-LSQ1GP24TSC0                OBJECT IDENTIFIER ::= { hpnicfevtModuleSwitchType 571 } -- 16-Port 1000BASE-X Gigabit Ethernet Optical(SFP,LC) And 8-Port 10/100/1000BASE-T RJ45/1000BASE-X SFP Combo Interface Board
hpnicfevtModuleSw-LSQ1ACGASC0                 OBJECT IDENTIFIER ::= { hpnicfevtModuleSwitchType 572 } -- Application Control Gateway Board
hpnicfevtModuleSw-LSD1XP1ES0                  OBJECT IDENTIFIER ::= { hpnicfevtModuleSwitchType 573 } -- 1-Port 10GBASE-X Ethernet XFP Optical Interface Card
hpnicfevtModuleSw-LSD1GP12ES0                 OBJECT IDENTIFIER ::= { hpnicfevtModuleSwitchType 574 } -- 12-Port 1000BASE-X Ethernet SFP Interface Card
hpnicfevtModuleSw-LSQ1SRP12GB0                OBJECT IDENTIFIER ::= { hpnicfevtModuleSwitchType 575 } -- Switch And Route Processing Unit with 12 1000BASE Ethernet Optical Interfaces(SFP,LC),Salience VI-GE
hpnicfevtModuleSw-LSQ1GV40PSC0                OBJECT IDENTIFIER ::= { hpnicfevtModuleSwitchType 576 } -- 40-Port 10/100/1000BASE-T Electrical(RJ45) And 8-Port 1000BASE-X Optical Ethernet Interface Board(SFP,LC),PoE
hpnicfevtModuleSw-LSQ1FWBSC1                  OBJECT IDENTIFIER ::= { hpnicfevtModuleSwitchType 577 } -- Firewall Board
hpnicfevtModuleSw-LSQ1NSMSC0                  OBJECT IDENTIFIER ::= { hpnicfevtModuleSwitchType 578 } -- NetStream Board
hpnicfevtModuleSw-LSQ1NSMSC1                  OBJECT IDENTIFIER ::= { hpnicfevtModuleSwitchType 579 } -- NetStream Board
hpnicfevtModuleSw-LSQ1AFDBSC0                 OBJECT IDENTIFIER ::= { hpnicfevtModuleSwitchType 580 } -- Anomaly Flow Detector Board
hpnicfevtModuleSw-LS81MPUB                    OBJECT IDENTIFIER ::= { hpnicfevtModuleSwitchType 581 } -- Salience IV
hpnicfevtModuleSw-LS81FP48XL                  OBJECT IDENTIFIER ::= { hpnicfevtModuleSwitchType 582 } -- 48-Port 100M Ethernet Optical Interface Module,(SFP,LC)
hpnicfevtModuleSw-LS81FT48XL                  OBJECT IDENTIFIER ::= { hpnicfevtModuleSwitchType 583 } -- 48-Port 10/100M Ethernet Electrical Interface Module(RJ45)
hpnicfevtModuleSw-LS81GP12XL                  OBJECT IDENTIFIER ::= { hpnicfevtModuleSwitchType 584 } -- 12-Port 1000/100M Ethernet Optical Interface Module(SFP,LC)
hpnicfevtModuleSw-LS81GP24XL                  OBJECT IDENTIFIER ::= { hpnicfevtModuleSwitchType 585 } -- 24-Port 1000/100M Ethernet Optical Interface Module(SFP,LC)
hpnicfevtModuleSw-LS81GP48XL                  OBJECT IDENTIFIER ::= { hpnicfevtModuleSwitchType 586 } -- 48-Port 1000/100M Ethernet Optical Interface Module(SFP,LC)
hpnicfevtModuleSw-LS81GT24XL                  OBJECT IDENTIFIER ::= { hpnicfevtModuleSwitchType 587 } -- 24-Port 10/100/1000M Ethernet Electrical Interface Module(RJ45)
hpnicfevtModuleSw-LS81GT48XL                  OBJECT IDENTIFIER ::= { hpnicfevtModuleSwitchType 588 } -- 48-Port 10/100/1000M Ethernet Electrical Interface Module(RJ45)
hpnicfevtModuleSw-LS81TGX2XL                  OBJECT IDENTIFIER ::= { hpnicfevtModuleSwitchType 589 } -- 2-Port 10GBASE Ethernet Optical Interface Module(XFP,LC)
hpnicfevtModuleSw-LSQ1GV48SD0                 OBJECT IDENTIFIER ::= { hpnicfevtModuleSwitchType 590 } -- 48-Port 1000Base-T Gigabit Ethernet Interface Board(RJ45),PoE
hpnicfevtModuleSw-LSQ1GP48EB0                 OBJECT IDENTIFIER ::= { hpnicfevtModuleSwitchType 591 } -- 48-Port Enhanced 1000BASE-X Ethernet Optical Interface Board(SFP,LC)
hpnicfevtModuleSw-LSQ1IPSSC0                  OBJECT IDENTIFIER ::= { hpnicfevtModuleSwitchType 592 } -- Gigabit IPS Card
hpnicfevtModuleSw-LSQ1GV48SD1                 OBJECT IDENTIFIER ::= { hpnicfevtModuleSwitchType 593 } -- 48-Port 1000Base-T Gigabit Ethernet Interface Board(RJ45),PoE
hpnicfevtModuleSw-LSQ1GP48SD0                 OBJECT IDENTIFIER ::= { hpnicfevtModuleSwitchType 594 } -- 48-Port 1000BASE-X Gigabit Ethernet Optical Interface(SFP,LC) Interface Board
hpnicfevtModuleSw-LSQ1GP48SD1                 OBJECT IDENTIFIER ::= { hpnicfevtModuleSwitchType 595 } -- 48-Port 1000BASE-X Gigabit Ethernet Optical Interface(SFP,LC) Interface Board
hpnicfevtModuleSw-LSQ1SRPA0                   OBJECT IDENTIFIER ::= { hpnicfevtModuleSwitchType 596 } -- Salience VI-Smart
hpnicfevtModuleSw-LSQ1SRPA1                   OBJECT IDENTIFIER ::= { hpnicfevtModuleSwitchType 597 } -- Salience VI-Smart
hpnicfevtModuleSw-LSQ2FP48SA0                 OBJECT IDENTIFIER ::= { hpnicfevtModuleSwitchType 598 } -- 48 Port 100M Ethernet Optical Interface Board(SFP,LC)
hpnicfevtModuleSw-LSQ2FP48SA1                 OBJECT IDENTIFIER ::= { hpnicfevtModuleSwitchType 599 } -- 48 Port 100M Ethernet Optical Interface Board(SFP,LC)
hpnicfevtModuleSw-LSQ2FT48SA0                 OBJECT IDENTIFIER ::= { hpnicfevtModuleSwitchType 600 } -- 48-Port 100M Ethernet Electrical Interface Switch Unit(RJ45)
hpnicfevtModuleSw-LSQ2FT48SA1                 OBJECT IDENTIFIER ::= { hpnicfevtModuleSwitchType 601 } -- 48-Port 100M Ethernet Electrical Interface Switch Unit(RJ45)
hpnicfevtModuleSw-LSQ1GV24PSC0                OBJECT IDENTIFIER ::= { hpnicfevtModuleSwitchType 602 } -- 24-Port 10/100/1000BASE-T Electrical(RJ45) Interface Board,including 4 Combo Ports,SFP Req,PoE,No Spell
hpnicfevtModuleSw-LSQ1GV24PSC1                OBJECT IDENTIFIER ::= { hpnicfevtModuleSwitchType 603 } -- 24-Port 10/100/1000BASE-T Electrical(RJ45) Interface Board,including 4 Combo Ports,SFP Req,PoE,No Spell
hpnicfevtModuleSw-LSQ1CGV24PSC0               OBJECT IDENTIFIER ::= { hpnicfevtModuleSwitchType 604 } -- Switching and Routing Processing Unit with 24 10/100/1000BASE-T Electrical Ports(RJ45),including 4 Combo Ports,SFP Req,PoE,No Spell
hpnicfevtModuleSw-LSQ1CGV24PSC1               OBJECT IDENTIFIER ::= { hpnicfevtModuleSwitchType 605 } -- Switching and Routing Processing Unit with 24 10/100/1000BASE-T Electrical Ports(RJ45),including 4 Combo Ports,SFP Req,PoE,No Spell
hpnicfevtModuleSw-LSQ1GP24TEB0                OBJECT IDENTIFIER ::= { hpnicfevtModuleSwitchType 606 } -- 16-Port 1000BASE-X Gigabit Ethernet Optical Interface(SFP,LC)+8-Port Combo Interface Board
hpnicfevtModuleSw-LSQ1GP24TEB1                OBJECT IDENTIFIER ::= { hpnicfevtModuleSwitchType 607 } -- 16-Port 1000BASE-X Gigabit Ethernet Optical Interface(SFP,LC)+8-Port Combo Interface Board
hpnicfevtModuleSw-LSQ1GP24TSD0                OBJECT IDENTIFIER ::= { hpnicfevtModuleSwitchType 608 } -- 16-Port 1000BASE-X Gigabit Ethernet Optical Interface(SFP,LC)+8-Port Combo Interface Board
hpnicfevtModuleSw-LSQ1GP24TSD1                OBJECT IDENTIFIER ::= { hpnicfevtModuleSwitchType 609 } -- 16-Port 1000BASE-X Gigabit Ethernet Optical Interface(SFP,LC)+8-Port Combo Interface Board
hpnicfevtModuleSw-LSQ1GP24TXSD0               OBJECT IDENTIFIER ::= { hpnicfevtModuleSwitchType 610 } -- 16-Port GE Optical Interface(SFP,LC)+8-Port Combo Interface+2-Port 10GE Optical Interface Board(XFP,LC)
hpnicfevtModuleSw-LSQ1GP24TXSD1               OBJECT IDENTIFIER ::= { hpnicfevtModuleSwitchType 611 } -- 16-Port GE Optical Interface(SFP,LC)+8-Port Combo Interface+2-Port 10GE Optical Interface Board(XFP,LC)
hpnicfevtModuleSw-LSQ1TGX2EB0                 OBJECT IDENTIFIER ::= { hpnicfevtModuleSwitchType 612 } -- 2-Port 10GBASE Ethernet Optical Interface Board(XFP,LC)
hpnicfevtModuleSw-LSQ1TGX2EB1                 OBJECT IDENTIFIER ::= { hpnicfevtModuleSwitchType 613 } -- 2-Port 10GBASE Ethernet Optical Interface Board(XFP,LC)
hpnicfevtModuleSw-LSQ1TGX2SD0                 OBJECT IDENTIFIER ::= { hpnicfevtModuleSwitchType 614 } -- 2-Port 10GBASE Ethernet Optical Interface Board(XFP,LC)
hpnicfevtModuleSw-LSQ1TGX2SD1                 OBJECT IDENTIFIER ::= { hpnicfevtModuleSwitchType 615 } -- 2-Port 10GBASE Ethernet Optical Interface Board(XFP,LC)
hpnicfevtModuleSw-LSQ1TGX4SD0                 OBJECT IDENTIFIER ::= { hpnicfevtModuleSwitchType 616 } -- 4-Port 10GBASE Ethernet Optical Interface Board(XFP,LC)
hpnicfevtModuleSw-LSQ1TGX4SD1                 OBJECT IDENTIFIER ::= { hpnicfevtModuleSwitchType 617 } -- 4-Port 10GBASE Ethernet Optical Interface Board(XFP,LC)
hpnicfevtModuleSw-LSQ1TGX8SD0                 OBJECT IDENTIFIER ::= { hpnicfevtModuleSwitchType 618 } -- 8-Port 10GBASE Ethernet Optical Interface Board(XFP,LC)
hpnicfevtModuleSw-LSQ1TGX8SD1                 OBJECT IDENTIFIER ::= { hpnicfevtModuleSwitchType 619 } -- 8-Port 10GBASE Ethernet Optical Interface Board(XFP,LC)
hpnicfevtModuleSw-LSQ1GP48EB1                 OBJECT IDENTIFIER ::= { hpnicfevtModuleSwitchType 620 } -- 48-Port Enhanced 1000BASE-X Ethernet Optical Interface Board(SFP,LC)
hpnicfevtModuleSw-LSQ1TGX4EB0                 OBJECT IDENTIFIER ::= { hpnicfevtModuleSwitchType 621 } -- 4-Port 10GBASE Ethernet Optical Interface Board(XFP,LC)
hpnicfevtModuleSw-LSQ1TGX4EB1                 OBJECT IDENTIFIER ::= { hpnicfevtModuleSwitchType 622 } -- 4-Port 10GBASE Ethernet Optical Interface Board(XFP,LC)
hpnicfevtModuleSw-LSQ1GP12SC3                 OBJECT IDENTIFIER ::= { hpnicfevtModuleSwitchType 623 } -- 12-Port 1000BASE-X Ethernet Optical Interface Board(SFP,LC)
hpnicfevtModuleSw-LSQ1GP24TSC3                OBJECT IDENTIFIER ::= { hpnicfevtModuleSwitchType 624 } -- 16-Port 1000BASE-X Gigabit Ethernet Optical(SFP,LC) And 8-Port 10/100/1000BASE-T RJ45/1000BASE-X SFP Combo Interface Board
hpnicfevtModuleSw-LSQ1GP48SC3                 OBJECT IDENTIFIER ::= { hpnicfevtModuleSwitchType 625 } -- 48-Port 1000BASE Ethernet Optical Interface Board(SFP,LC)
hpnicfevtModuleSw-LSQ1GV48SC3                 OBJECT IDENTIFIER ::= { hpnicfevtModuleSwitchType 626 } -- 48-Port 1000Base-T Gigabit Ethernet Interface Board(RJ45),PoE
hpnicfevtModuleSw-LSQ1MPUA3                   OBJECT IDENTIFIER ::= { hpnicfevtModuleSwitchType 627 } -- Master Process Board
hpnicfevtModuleSw-LSQ1SRP1CB3                 OBJECT IDENTIFIER ::= { hpnicfevtModuleSwitchType 628 } -- Salience VI-Turbo
hpnicfevtModuleSw-LSQ1SRPA3                   OBJECT IDENTIFIER ::= { hpnicfevtModuleSwitchType 629 } -- Salience VI-Smart
hpnicfevtModuleSw-LSQ2FP48SA3                 OBJECT IDENTIFIER ::= { hpnicfevtModuleSwitchType 630 } -- 48 Port 100M Ethernet Optical Interface Board(SFP,LC)
hpnicfevtModuleSw-LSQ2FT48SA3                 OBJECT IDENTIFIER ::= { hpnicfevtModuleSwitchType 631 } -- 48-Port 100M Ethernet Electrical Interface Switch Unit(RJ45)
hpnicfevtModuleSw-LSQ1MPUB3                   OBJECT IDENTIFIER ::= { hpnicfevtModuleSwitchType 632 } -- Salience VI-Lite
hpnicfevtModuleSw-LSQ1CGP24TSC3               OBJECT IDENTIFIER ::= { hpnicfevtModuleSwitchType 633 } -- Switching and Routing Processing Unit with 24 1000BASE-X Gigabit Ethernet Optical Ports,including 8 Combo Ports,SFP Req.
hpnicfevtModuleSw-LSQ1MPUB4                   OBJECT IDENTIFIER ::= { hpnicfevtModuleSwitchType 634 } -- Salience VI-Lite
hpnicfevtModuleSw-LSQ1SRPD4                   OBJECT IDENTIFIER ::= { hpnicfevtModuleSwitchType 635 } -- Salience VI-Plus
hpnicfevtModuleSw-LSQ1SSLSC0                  OBJECT IDENTIFIER ::= { hpnicfevtModuleSwitchType 636 } -- SSL VPN Service Board(B)
hpnicfevtModuleSw-LSQ1LBSC0                   OBJECT IDENTIFIER ::= { hpnicfevtModuleSwitchType 637 } -- Gigabit Load Balancing Card
hpnicfevtModuleSw-LSQ1NAT24SC0                OBJECT IDENTIFIER ::= { hpnicfevtModuleSwitchType 638 } -- NAT/NetStream-Supported Line Processing Unit with 24 10/100/1000BASE-T Electrical Ports(RJ45),including Combo Ports,Upgradeable to PoE
hpnicfevtModuleSw-LSQ1SRP12GB4                OBJECT IDENTIFIER ::= { hpnicfevtModuleSwitchType 639 } -- Salience VI-GE
hpnicfevtModuleSw-LSQ1TGS8SC0                 OBJECT IDENTIFIER ::= { hpnicfevtModuleSwitchType 640 } -- 8-Port 10GBASE Ethernet SFP+ Optical Interface Board
hpnicfevtModuleSw-LSQ3PT4PSC0                 OBJECT IDENTIFIER ::= { hpnicfevtModuleSwitchType 641 } -- 4-Port 1000Base-PX Optical Line Terminal(EPON OLT SFP,SC)+8-Port 1000BASE-X Optical Interface Board(SFP,LC)
hpnicfevtModuleSw-EWPXM2MPUB0                 OBJECT IDENTIFIER ::= { hpnicfevtModuleSwitchType 642 } -- Salience VI-Lite
hpnicfevtModuleSw-EWPXM2SRP12GB0              OBJECT IDENTIFIER ::= { hpnicfevtModuleSwitchType 643 } -- Salience VI-GE
hpnicfevtModuleSw-EWPXM2SRPD0                 OBJECT IDENTIFIER ::= { hpnicfevtModuleSwitchType 644 } -- Salience VI-Plus
hpnicfevtModuleSw-EWPXM2GP24TSD0              OBJECT IDENTIFIER ::= { hpnicfevtModuleSwitchType 645 } -- 16-Port 1000BASE-X Ethernet Optical Interface(SFP Req.)+8-Port Combo Interface Module
hpnicfevtModuleSw-EWPXM2GP24TXSD0             OBJECT IDENTIFIER ::= { hpnicfevtModuleSwitchType 646 } -- 16-Port 1000BASE-X Ethernet Optical Interface(SFP Req.)+8-Port Combo Interface+2-Port 10GE Optical Interface(XFP Req.) Module
hpnicfevtModuleSw-EWPXM2TGX4SD0               OBJECT IDENTIFIER ::= { hpnicfevtModuleSwitchType 647 } -- 4-Port 10GBASE Ethernet Optical Interface Module,XFP Req
hpnicfevtModuleSw-EWPXM2GP48SD0               OBJECT IDENTIFIER ::= { hpnicfevtModuleSwitchType 648 } -- 48-Port 1000BASE-X Gigabit Ethernet Optical Interface Module,SFP Req
hpnicfevtModuleSw-EWPXM2GP24TSC0              OBJECT IDENTIFIER ::= { hpnicfevtModuleSwitchType 649 } -- 24-Port 1000BASE-X/100BASE-FX Optical  Interface Module,including 8 Combo Ports,SFP Req
hpnicfevtModuleSw-EWPXM2TGX2SC0               OBJECT IDENTIFIER ::= { hpnicfevtModuleSwitchType 650 } -- 2-Port 10GBASE Ethernet Optical Interface Module,XFP Req
hpnicfevtModuleSw-EWPXM2GP48SC0               OBJECT IDENTIFIER ::= { hpnicfevtModuleSwitchType 651 } -- 48-Port 1000BASE-X/100BASE-FX Ethernet Optical Interface Module,SFP Req
hpnicfevtModuleSw-LS7500-GP48-SC              OBJECT IDENTIFIER ::= { hpnicfevtModuleSwitchType 652 } -- 48-Port 1000BASE-X/100BASE-FX Ethernet Optical Interface Module(SFP,LC)
hpnicfevtModuleSw-LS7500-GP48-SD              OBJECT IDENTIFIER ::= { hpnicfevtModuleSwitchType 653 } -- 48-Port 1000BASE-X Gigabit Ethernet Optical Interface Module(SFP,LC)
hpnicfevtModuleSw-LS7500-GT48-SC              OBJECT IDENTIFIER ::= { hpnicfevtModuleSwitchType 654 } -- 48-Port 10/100/1000BASE-TX Ethernet Interface Module(RJ45)
hpnicfevtModuleSw-LS7500-GT48-SD              OBJECT IDENTIFIER ::= { hpnicfevtModuleSwitchType 655 } -- 48-Port 10/100/1000BASE-T Ethernet Interface Module(RJ45)
hpnicfevtModuleSw-LS7500-SRPG1                OBJECT IDENTIFIER ::= { hpnicfevtModuleSwitchType 656 } -- Main Control Unit
hpnicfevtModuleSw-LS7500-SRPG2                OBJECT IDENTIFIER ::= { hpnicfevtModuleSwitchType 657 } -- Salience VI-Lite
hpnicfevtModuleSw-LS7500-XP4-SD               OBJECT IDENTIFIER ::= { hpnicfevtModuleSwitchType 658 } -- 4-Port 10GBASE Ethernet Optical Interface Module(XFP,LC)
hpnicfevtModuleSw-LS7500-XP8-SD               OBJECT IDENTIFIER ::= { hpnicfevtModuleSwitchType 659 } -- 8-Port 10GBASE Ethernet Optical Interface Module(XFP,LC)
hpnicfevtModuleSw-LSQ4PT4PSC0                 OBJECT IDENTIFIER ::= { hpnicfevtModuleSwitchType 660 } -- 4-Port 1000Base-PX Optical Line Terminal(EPON OLT SFP,SC)+8-Port 1000BASE-X Optical Interface Board(SFP,LC)
hpnicfevtModuleSw-LSQ4PT8PSC0                 OBJECT IDENTIFIER ::= { hpnicfevtModuleSwitchType 661 } -- 8-Port 1000Base-PX Optical Line Terminal(EPON OLT SFP,SC)+8-Port 1000BASE-X Optical Interface Board(SFP,LC)
hpnicfevtModuleSw-LSQ4PT16PSC0                OBJECT IDENTIFIER ::= { hpnicfevtModuleSwitchType 662 } -- 16-Port 1000Base-PX Optical Line Terminal(EPON OLT SFP,SC)+8-Port 1000BASE-X Optical Interface Board(SFP,LC)
hpnicfevtModuleSw-LSQ1GP24TSA0                OBJECT IDENTIFIER ::= { hpnicfevtModuleSwitchType 663 } -- 16-Port 1000BASE-X Gigabit Ethernet Optical(SFP,LC) And 8-Port 10/100/1000BASE-T RJ45/1000BASE-X SFP Combo Interface Board
hpnicfevtModuleSw-LSQ1GV24PSA0                OBJECT IDENTIFIER ::= { hpnicfevtModuleSwitchType 664 } -- 24-Port 10/100/1000BASE-T Electrical(RJ45) Interface Board,including 4 Combo Ports,SFP Req,Upgradeable to PoE
hpnicfevtModuleSw-LSQ1SRPD3                   OBJECT IDENTIFIER ::= { hpnicfevtModuleSwitchType 665 } -- Salience VI-Plus
hpnicfevtModuleSw-LSQ1SUPA0                   OBJECT IDENTIFIER ::= { hpnicfevtModuleSwitchType 666 } -- Supervisor Engine Board
hpnicfevtModuleSw-LSU1FAB04A0                 OBJECT IDENTIFIER ::= { hpnicfevtModuleSwitchType 667 } -- Switch Fabric Board
hpnicfevtModuleSw-LSU1FAB08A0                 OBJECT IDENTIFIER ::= { hpnicfevtModuleSwitchType 668 } -- Switch Fabric Board
hpnicfevtModuleSw-LSU1TGS8EA0                 OBJECT IDENTIFIER ::= { hpnicfevtModuleSwitchType 669 } -- 8-Port 10GBASE Ethernet SFP+ Optical Interface Board(EA)
hpnicfevtModuleSw-LSU1TGS8EB0                 OBJECT IDENTIFIER ::= { hpnicfevtModuleSwitchType 670 } -- 8-Port 10GBASE Ethernet SFP+ Optical Interface Board
hpnicfevtModuleSw-LSU1TGS8SE0                 OBJECT IDENTIFIER ::= { hpnicfevtModuleSwitchType 671 } -- 8-Port 10GBASE Ethernet SFP+ Optical Interface Board(SE)
hpnicfevtModuleSw-LSUTGS16SC0                 OBJECT IDENTIFIER ::= { hpnicfevtModuleSwitchType 672 } -- 16-Port 10GBASE Ethernet SFP+ Optical Interface Board
hpnicfevtModuleSw-LSU1SUPA0                   OBJECT IDENTIFIER ::= { hpnicfevtModuleSwitchType 673 } -- Supervisor Engine Board
hpnicfevtModuleSw-LSU1GP24TXEA0               OBJECT IDENTIFIER ::= { hpnicfevtModuleSwitchType 674 } -- 16-Port 1000BASE-X Optical Interface(SFP,LC)+8-Port Combo Interface+2-Port 10GE Optical Interface Board(XFP,LC)(EA)
hpnicfevtModuleSw-LSU1GP24TXEB0               OBJECT IDENTIFIER ::= { hpnicfevtModuleSwitchType 675 } -- 16-Port 1000BASE-X Optical Interface(SFP,LC)+8-Port Combo Interface+2-Port 10GE Optical Interface Board(XFP,LC)(EB)
hpnicfevtModuleSw-LSU1GP24TXSE0               OBJECT IDENTIFIER ::= { hpnicfevtModuleSwitchType 676 } -- 16-Port 1000BASE-X Optical Interface(SFP,LC)+8-Port Combo Interface+2-Port 10GE Optical Interface Board(XFP,LC)(SE)
hpnicfevtModuleSw-LSU1GP48EA0                 OBJECT IDENTIFIER ::= { hpnicfevtModuleSwitchType 677 } -- 48-Port 1000BASE-X Gigabit Ethernet Optical Interface(SFP,LC) Interface Board(EA)
hpnicfevtModuleSw-LSU1GP48EB0                 OBJECT IDENTIFIER ::= { hpnicfevtModuleSwitchType 678 } -- 48-Port Enhanced 1000BASE-X Ethernet Optical Interface Board(SFP,LC)(EB)
hpnicfevtModuleSw-LSU1GP48SE0                 OBJECT IDENTIFIER ::= { hpnicfevtModuleSwitchType 679 } -- 48-Port 1000BASE Ethernet Optical Interface Board(SFP,LC)(SE)
hpnicfevtModuleSw-LSU1GT48EA0                 OBJECT IDENTIFIER ::= { hpnicfevtModuleSwitchType 680 } -- 48-Port 1000Base-T Gigabit Ethernet Interface Board(RJ45)(EA)
hpnicfevtModuleSw-LSU1GT48SE0                 OBJECT IDENTIFIER ::= { hpnicfevtModuleSwitchType 681 } -- 48-Port 1000Base-T Gigabit Ethernet Interface Board(RJ45)(SE)
hpnicfevtModuleSw-LSU1TGX4EA0                 OBJECT IDENTIFIER ::= { hpnicfevtModuleSwitchType 682 } -- 4-Port 10GBASE Ethernet Optical Interface Board(XFP,LC)(EA)
hpnicfevtModuleSw-LSU1TGX4EB0                 OBJECT IDENTIFIER ::= { hpnicfevtModuleSwitchType 683 } -- 4-Port 10GBASE Ethernet Optical Interface Board(XFP,LC)(EB)
hpnicfevtModuleSw-LSU1TGX4SE0                 OBJECT IDENTIFIER ::= { hpnicfevtModuleSwitchType 684 } -- 4-Port 10GBASE Ethernet Optical Interface Board(XFP,LC)(SE)
hpnicfevtModuleSw-LSQ1FAB08A0                 OBJECT IDENTIFIER ::= { hpnicfevtModuleSwitchType 685 } -- Switching Fabric Board
hpnicfevtModuleSw-EWPX2WCMD0                  OBJECT IDENTIFIER ::= { hpnicfevtModuleSwitchType 686 } -- Access Controller Card
hpnicfevtModuleSw-LSQ1WCMD0                   OBJECT IDENTIFIER ::= { hpnicfevtModuleSwitchType 687 } -- Access Controller Card
hpnicfevtModuleSw-LSQ1IAGSC0                  OBJECT IDENTIFIER ::= { hpnicfevtModuleSwitchType 688 } -- Wireless&IAG Service Card
hpnicfevtModuleSw-LSU1GP24TSE0                OBJECT IDENTIFIER ::= { hpnicfevtModuleSwitchType 689 } -- 16-Port 1000BASE-X Optical Interface(SFP,LC)+8-Port Combo Interface Board(SE)
hpnicfevtModuleSw-LSQ1TGS16SC0                OBJECT IDENTIFIER ::= { hpnicfevtModuleSwitchType 690 } -- 16-Port 10GBASE Ethernet SFP+ Optical Interface Board
hpnicfevtModuleSw-EWPX2TGS16SC0               OBJECT IDENTIFIER ::= { hpnicfevtModuleSwitchType 691 } -- 16-Port 10GBASE Ethernet SFP+ Optical Interface Board
hpnicfevtModuleSw-LSQ1SUPA3                   OBJECT IDENTIFIER ::= { hpnicfevtModuleSwitchType 692 } -- Supervisor Engine Board
hpnicfevtModuleSw-LSQ1FAB04A3                 OBJECT IDENTIFIER ::= { hpnicfevtModuleSwitchType 693 } -- 320G Switch Fabric Board
hpnicfevtModuleSw-LSQ1FAB08A3                 OBJECT IDENTIFIER ::= { hpnicfevtModuleSwitchType 694 } -- 640G Switch Fabric Board
hpnicfevtModuleSw-LSQ1GT48SC0                 OBJECT IDENTIFIER ::= { hpnicfevtModuleSwitchType 695 } -- 48-Port 1000Base-T Gigabit Ethernet Interface Board(RJ45)
hpnicfevtModuleSw-LSR2SRP2C1                  OBJECT IDENTIFIER ::= { hpnicfevtModuleSwitchType 696 } -- Management and Route Process Unit
hpnicfevtModuleSw-LSR2SRP2C2                  OBJECT IDENTIFIER ::= { hpnicfevtModuleSwitchType 697 } -- Management and Route Process Unit

--
-- 700 to 799 reserved for primary switches
--
hpnicfevtModuleSw-1000BASE-X-COMBO            OBJECT IDENTIFIER ::= { hpnicfevtModuleSwitchType 701 } -- Single port 10/100/1000BASE-T/1000BASE-X Combo Interface Board
hpnicfevtModuleSw-EPON-1000M                  OBJECT IDENTIFIER ::= { hpnicfevtModuleSwitchType 702 } -- Optical Network Unit Interface Board
hpnicfevtModuleSw-1000BASE-FIXED-2SFP-T-2RJ45         OBJECT IDENTIFIER ::= { hpnicfevtModuleSwitchType 703 } -- 2 port 10/100/1000BASE-T and 2 port 1000BASE-X Interface Board
hpnicfevtModuleSw-100M-1550-BIDI              OBJECT IDENTIFIER ::= { hpnicfevtModuleSwitchType 704 }  -- 100BASE-X BIDI Interface Board, Tx 1550nm, Rx 1310nm
hpnicfevtModuleSw-100M-1310-BIDI              OBJECT IDENTIFIER ::= { hpnicfevtModuleSwitchType 705 }  -- 100BASE-X reverse Interface Board, Tx 1310nm, Rx 1550nm
hpnicfevtModuleSw-1000BASE-FIXED-4RJ45-4SFP-COMBO     OBJECT IDENTIFIER ::= { hpnicfevtModuleSwitchType 706 } -- 4 port 10/100/1000BASE-T and 4 port 1000BASE-X COMBO Interface Board
hpnicfevtModuleSw-LSH1PK2T                    OBJECT IDENTIFIER ::= { hpnicfevtModuleSwitchType 707 } -- OSM Interface Board
hpnicfevtModuleSw-LSPM2GP2P                   OBJECT IDENTIFIER ::= { hpnicfevtModuleSwitchType 708 } -- 2-Port 1000BASE-X SFP Module
hpnicfevtModuleSw-LSWM1GT16P                  OBJECT IDENTIFIER ::= { hpnicfevtModuleSwitchType 709 } -- 16-Port 10/100/1000BASE-T Ethernet Electrical Interface Module
hpnicfevtModuleSw-LSWM1GP16P                  OBJECT IDENTIFIER ::= { hpnicfevtModuleSwitchType 710 } -- 16-Port 100/1000BASE-X Ethernet Optical Interface Module
hpnicfevtModuleSw-LSWM1XP2P                   OBJECT IDENTIFIER ::= { hpnicfevtModuleSwitchType 711 } -- 2-Port 10G Ethernet XFP Optical Interface Module
hpnicfevtModuleSw-LSWM1XP4P                   OBJECT IDENTIFIER ::= { hpnicfevtModuleSwitchType 712 } -- 4-Port 10G Ethernet XFP Optical Interface Module
hpnicfevtModuleSw-LSWM1SP2P                   OBJECT IDENTIFIER ::= { hpnicfevtModuleSwitchType 713 } -- 2-Port 10G Ethernet SFP PLUS Optical Interface Module
hpnicfevtModuleSw-LSWM1SP4P                   OBJECT IDENTIFIER ::= { hpnicfevtModuleSwitchType 714 } -- 4-Port 10G Ethernet SFP PLUS Optical Interface Module
hpnicfevtModuleSw-LSWM148POEM                 OBJECT IDENTIFIER ::= { hpnicfevtModuleSwitchType 715 } -- 48 Port Mid Power PoE Module
hpnicfevtModuleSw-LSWM1FW10                   OBJECT IDENTIFIER ::= { hpnicfevtModuleSwitchType 716 } -- RMI CPU XLR 732, with Firewall software
hpnicfevtModuleSw-LSWM1WCM10                  OBJECT IDENTIFIER ::= { hpnicfevtModuleSwitchType 717 } -- RMI CPU XLR 732, with Wireless Access Controller software
hpnicfevtModuleSw-LSWM1IPS10                  OBJECT IDENTIFIER ::= { hpnicfevtModuleSwitchType 718 } -- RMI CPU XLR 732, with IPS/AV software
hpnicfevtModuleSw-LSWM1WCM20                  OBJECT IDENTIFIER ::= { hpnicfevtModuleSwitchType 719 } -- RMI CPU XLR 408, with Wireless Access Controller software
hpnicfevtModuleSw-IPS-T1000-M                 OBJECT IDENTIFIER ::= { hpnicfevtModuleSwitchType 720 } -- IPS for T1000-M mainboard module
hpnicfevtModuleSw-IPS-T1000-A                 OBJECT IDENTIFIER ::= { hpnicfevtModuleSwitchType 721 } -- IPS for T1000-A mainboard module
hpnicfevtModuleSw-IPS-T1000-S                 OBJECT IDENTIFIER ::= { hpnicfevtModuleSwitchType 722 } -- IPS for T1000-S mainboard module
hpnicfevtModuleSw-IPS-GX4C                    OBJECT IDENTIFIER ::= { hpnicfevtModuleSwitchType 723 } -- four-port-gigabit-fiber-board-module
hpnicfevtModuleSw-IPS-GT4C                    OBJECT IDENTIFIER ::= { hpnicfevtModuleSwitchType 724 } -- four-port-1000BASET-board-module
hpnicfevtModuleSw-LSPM2SP2P                   OBJECT IDENTIFIER ::= { hpnicfevtModuleSwitchType 725 } -- 2-Port 10G Ethernet SFP PLUS Optical Interface Module
hpnicfevtModuleSw-LSPM2SP2PA                  OBJECT IDENTIFIER ::= { hpnicfevtModuleSwitchType 726 } -- 2-Port Second Version SFP+ Module
hpnicfevtModuleSw-LSP5GP8P                    OBJECT IDENTIFIER ::= { hpnicfevtModuleSwitchType 727 } -- 8-Port 1G Ethernet SFP Optical Interface Module
hpnicfevtModuleSw-LSP5GT8P                    OBJECT IDENTIFIER ::= { hpnicfevtModuleSwitchType 728 } -- 8-Port 10/100/1000BASE-T Ethernet Electrical Interface Module
hpnicfevtModuleSw-LSWM1FC4P                   OBJECT IDENTIFIER ::= { hpnicfevtModuleSwitchType 729 } -- 4-Port 8G Fibre Channel Interface Module
hpnicfevtModuleSw-LSW1XGT4P0                  OBJECT IDENTIFIER ::= { hpnicfevtModuleSwitchType 730 } -- 4-Port 10G Ethernet Copper Interface Module
hpnicfevtModuleSw-LSW1XGT2P0                  OBJECT IDENTIFIER ::= { hpnicfevtModuleSwitchType 731 } -- 2-Port 10G Ethernet Copper Interface Module
hpnicfevtModuleSw-LSP1XGT2P                   OBJECT IDENTIFIER ::= { hpnicfevtModuleSwitchType 732 } -- 2-Port 10G Ethernet Copper Interface Board
hpnicfevtModuleSw-LSPM3XGT2P                  OBJECT IDENTIFIER ::= { hpnicfevtModuleSwitchType 733 } -- 2-Port 1/10G BASE-T Ethernet Copper Interface Module
hpnicfevtModuleSw-LSWM2QP2P                   OBJECT IDENTIFIER ::= { hpnicfevtModuleSwitchType 734 } -- 2-Port QSFP+ Interface Module
hpnicfevtModuleSw-LSWM2XGT2PM                 OBJECT IDENTIFIER ::= { hpnicfevtModuleSwitchType 735 } -- 2-Port 10G Ethernet Copper Interface Module with MACsec
hpnicfevtModuleSw-LSWM2SP2PM                  OBJECT IDENTIFIER ::= { hpnicfevtModuleSwitchType 736 } -- 2-Port SFP+ Interface Module with MACsec
hpnicfevtModuleSw-LSWM2SP8PM                  OBJECT IDENTIFIER ::= { hpnicfevtModuleSwitchType 737 } -- 8-Port SFP+ Interface Module with MACsec
hpnicfevtModuleSw-LSWM2SP8P                   OBJECT IDENTIFIER ::= { hpnicfevtModuleSwitchType 738 } -- 8-Port SFP+ Interface Module
hpnicfevtModuleSw-LSWM2XGT8PM                 OBJECT IDENTIFIER ::= { hpnicfevtModuleSwitchType 739 } -- 8-Port 10G Ethernet Copper Interface Module with MACsec
hpnicfevtModuleSw-LSWM18QC                    OBJECT IDENTIFIER ::= { hpnicfevtModuleSwitchType 740 } -- 8-Port QSFP+ Module
hpnicfevtModuleSw-LSWM124XG2Q                 OBJECT IDENTIFIER ::= { hpnicfevtModuleSwitchType 741 } -- 24-Port SFP+ and 2-Port QSFP+ Module
hpnicfevtModuleSw-LSWM124XGT2Q                OBJECT IDENTIFIER ::= { hpnicfevtModuleSwitchType 742 } -- 24-Port 10G BASE-T and 2-Port QSFP+ Module
hpnicfevtModuleSw-LSWM124XG2QL                OBJECT IDENTIFIER ::= { hpnicfevtModuleSwitchType 743 } -- 24-Port SFP+ and 2-Port QSFP+ Module

--
-- 800 to 899 reserved for WLAN products
--
hpnicfevtModuleSw-WX5002MPU                   OBJECT IDENTIFIER ::= { hpnicfevtModuleSwitchType 800 } -- Wireless Lan Control Board with 2-port 1000BASE-T/1000BASE-X Combo Interface
hpnicfevtModuleSw-LS8M1WCMA                   OBJECT IDENTIFIER ::= { hpnicfevtModuleSwitchType 801 } -- Wireless Lan Service Board
hpnicfevtModuleSw-EWPX1G24XA0                 OBJECT IDENTIFIER ::= { hpnicfevtModuleSwitchType 802 } -- 24-Port 1000BASE-T Gigabit Ethernet Interface(RJ45) and 4-port 1000BASE-T/1000BASE-X Combo Interface and 2-port 10GBASE Interface Line Card
hpnicfevtModuleSw-LSQ1WCMB0                   OBJECT IDENTIFIER ::= { hpnicfevtModuleSwitchType 803 } -- 1 Port 10GBASE Interface Board
hpnicfevtModuleSw-LSB1WCM2A0                  OBJECT IDENTIFIER ::= { hpnicfevtModuleSwitchType 804 } -- Wireless Controller Module Board
hpnicfevtModuleSw-EWPX1WCMB0                  OBJECT IDENTIFIER ::= { hpnicfevtModuleSwitchType 805 } -- 1 Port 10GBASE Interface Board
hpnicfevtModuleSw-EWPX1G24XC0                 OBJECT IDENTIFIER ::= { hpnicfevtModuleSwitchType 806 } -- 24-Port 1000BASE-T Gigabit Ethernet Interface(RJ45) and 4-port 1000BASE-T/1000BASE-X Combo Interface Line Card
hpnicfevtModuleSw-EWPX1WCMC0                  OBJECT IDENTIFIER ::= { hpnicfevtModuleSwitchType 807 } -- 1-Port 1000BASE-T Gigabit Ethernet of wireless Lan Service Board
hpnicfevtModuleSw-EWPX1FWA0                   OBJECT IDENTIFIER ::= { hpnicfevtModuleSwitchType 808 } -- Firewall Service Board
hpnicfevtModuleSw-EWPX1G10XC0                 OBJECT IDENTIFIER ::= { hpnicfevtModuleSwitchType 809 } -- 8-Port 1000BASE-T Gigabit Ethernet Interface(RJ45) and 2-port 1000BASE-X SFP Interface Line Card
hpnicfevtModuleSw-EWPX1WCM10C0                OBJECT IDENTIFIER ::= { hpnicfevtModuleSwitchType 810 } -- 1-Port 1000BASE-T Gigabit Ethernet of wireless Lan Service Board
hpnicfevtModuleSw-LSR1WCM2A1                  OBJECT IDENTIFIER ::= { hpnicfevtModuleSwitchType 811 } -- 1-Port 1000BASE-T Gigabit Ethernet of wireless Lan Service Board
hpnicfevtModuleSw-EWPX1WAP0                   OBJECT IDENTIFIER ::= { hpnicfevtModuleSwitchType 812 } -- Encryption Card
hpnicfevtModuleSw-EWPX1WCMD0                  OBJECT IDENTIFIER ::= { hpnicfevtModuleSwitchType 813 } -- 2 Port 10GBASE Interface Board
hpnicfevtModuleSw-EWPX1G24XCE0                OBJECT IDENTIFIER ::= { hpnicfevtModuleSwitchType 814 } -- 24-Port 1000BASE-T Gigabit Ethernet Interface(RJ45) and 4-port 1000BASE-T/1000BASE-X Combo Interface Line Card
hpnicfevtModuleSw-EWPX1WCMCE0                 OBJECT IDENTIFIER ::= { hpnicfevtModuleSwitchType 815 } -- 2-Port 1000BASE-T Gigabit Ethernet of wireless Lan Service Board
hpnicfevtModuleSw-EWPX1G24XD0                 OBJECT IDENTIFIER ::= { hpnicfevtModuleSwitchType 816 } -- 4-Port 10GBASE-T and 24-Port 1000BASE-T Gigabit Ethernet of wireless Lan Service Board

--
-- 900 to 1199 reserved for advanced switches part II
--
hpnicfevtModuleSw-LSR1DRSP2L1                 OBJECT IDENTIFIER ::= { hpnicfevtModuleSwitchType 900 } -- 2-Port OC-48c/STM-16c RPR Optical Interface Card,(SFP,LC)
hpnicfevtModuleSw-PIC-CLF2G8L                 OBJECT IDENTIFIER ::= { hpnicfevtModuleSwitchType 901 } -- 2-Port 155M CPOS Optical Interface(SFP,LC)+8-Port 1000BASE-X Optical Interface Card(SFP,LC)
hpnicfevtModuleSw-PIC-CLF4G8L                 OBJECT IDENTIFIER ::= { hpnicfevtModuleSwitchType 902 } -- 4-Port 155M CPOS Optical Interface(SFP,LC)+8-Port 1000BASE-X Optical Interface Card(SFP,LC)
hpnicfevtModuleSw-SR02SRP2F3                  OBJECT IDENTIFIER ::= { hpnicfevtModuleSwitchType 903 } -- Routing Switch Processing Board(2F)
hpnicfevtModuleSw-SR02SRP1F3                  OBJECT IDENTIFIER ::= { hpnicfevtModuleSwitchType 904 } -- Routing Switch Processing Board(1F)
hpnicfevtModuleSw-LST1GT48LEA1                OBJECT IDENTIFIER ::= { hpnicfevtModuleSwitchType 905 } -- 48-Port 10/100/1000BASE-T Interface Module(LEA),(RJ45)
hpnicfevtModuleSw-LST1GP48LEA1                OBJECT IDENTIFIER ::= { hpnicfevtModuleSwitchType 906 } -- 48-Port 1000BASE-X Interface Module(LEA),(SFP,LC)
hpnicfevtModuleSw-LST2XP8LEA1                 OBJECT IDENTIFIER ::= { hpnicfevtModuleSwitchType 907 } -- 8-Port 10GBASE-R Interface Module(LEA),(SFP+,LC)
hpnicfevtModuleSw-LST1GT48LEY1                OBJECT IDENTIFIER ::= { hpnicfevtModuleSwitchType 908 } -- 48-Port 10/100/1000BASE-T Interface Module(LEY),(RJ45)
hpnicfevtModuleSw-LST1GP48LEY1                OBJECT IDENTIFIER ::= { hpnicfevtModuleSwitchType 909 } -- 48-Port 1000BASE-X Interface Module(LEY),(SFP,LC)
hpnicfevtModuleSw-LST1XP32REY1                OBJECT IDENTIFIER ::= { hpnicfevtModuleSwitchType 910 } -- 32-Port 10GBASE-R Interface Module(REY),(SFP+,LC)
hpnicfevtModuleSw-LST1XP8LEY1                 OBJECT IDENTIFIER ::= { hpnicfevtModuleSwitchType 911 } -- 8-Port 10GBASE-R/W Interface Module(LEY),(XFP,LC)
hpnicfevtModuleSw-LST1GP48LEZ1                OBJECT IDENTIFIER ::= { hpnicfevtModuleSwitchType 912 } -- 48-Port 1000BASE-X Interface Module(LEZ),(SFP,LC)
hpnicfevtModuleSw-LST1XP8LEZ1                 OBJECT IDENTIFIER ::= { hpnicfevtModuleSwitchType 913 } -- 8-Port 10GBASE-R/W Interface Module(LEZ),(XFP,LC)
hpnicfevtModuleSw-IM-FW-II                    OBJECT IDENTIFIER ::= { hpnicfevtModuleSwitchType 914 } -- Firewall Service Processing Board-II
hpnicfevtModuleSw-IM-IPS                      OBJECT IDENTIFIER ::= { hpnicfevtModuleSwitchType 915 } -- Intrusion Prevention System Service Processing Board
hpnicfevtModuleSw-IM-SSL                      OBJECT IDENTIFIER ::= { hpnicfevtModuleSwitchType 916 } -- SSL VPN Service Processing Board
hpnicfevtModuleSw-IM-LB                       OBJECT IDENTIFIER ::= { hpnicfevtModuleSwitchType 917 } -- Load Balance Service Processing Board
hpnicfevtModuleSw-IM-ACG                      OBJECT IDENTIFIER ::= { hpnicfevtModuleSwitchType 918 } -- Application Control Gateway Service Processing Board
hpnicfevtModuleSw-LSR1XP16REC1                OBJECT IDENTIFIER ::= { hpnicfevtModuleSwitchType 919 } -- 16-Port 10GBASE-R Interface Module(REC),(SFP+,LC)
hpnicfevtModuleSw-LST2XP8LEB1                 OBJECT IDENTIFIER ::= { hpnicfevtModuleSwitchType 920 } -- 8-Port 10GBASE-R/W Interface Module(LEB),(XFP,LC)
hpnicfevtModuleSw-LST2XP8LEC1                 OBJECT IDENTIFIER ::= { hpnicfevtModuleSwitchType 921 } -- 8-Port 10GBASE-R/W Interface Module(LEC),(XFP,LC)
hpnicfevtModuleSw-LST2XP8LEF1                 OBJECT IDENTIFIER ::= { hpnicfevtModuleSwitchType 922 } -- 8-Port 10GBASE-R/W Interface Module(LEF),(XFP,LC)
hpnicfevtModuleSw-LSR2XP4LEB1                 OBJECT IDENTIFIER ::= { hpnicfevtModuleSwitchType 923 } -- 4-Port 10GBase-R/W Interface Module(LEB),(XFP,LC)
hpnicfevtModuleSw-LSR2XP4LEC1                 OBJECT IDENTIFIER ::= { hpnicfevtModuleSwitchType 924 } -- 4-Port 10GBase-R/W Interface Module(LEC),(XFP,LC)
hpnicfevtModuleSw-LST2XP32REB1                OBJECT IDENTIFIER ::= { hpnicfevtModuleSwitchType 925 } -- 32-Port 10GBASE-R Interface Module(REB),(SFP+,LC)
hpnicfevtModuleSw-LST2XP32REC1                OBJECT IDENTIFIER ::= { hpnicfevtModuleSwitchType 926 } -- 32-Port 10GBASE-R Interface Module(REC),(SFP+,LC)
hpnicfevtModuleSw-LSR1WCM3A1                  OBJECT IDENTIFIER ::= { hpnicfevtModuleSwitchType 927 } -- Access Controller Module
hpnicfevtModuleSw-LST1XP16LEB1                OBJECT IDENTIFIER ::= { hpnicfevtModuleSwitchType 928 } -- 16-Port 10GBASE-R Interface Module (LEB),(SFP+,LC)
hpnicfevtModuleSw-LST1XP16LEC1                OBJECT IDENTIFIER ::= { hpnicfevtModuleSwitchType 929 } -- 16-Port 10GBASE-R Interface Module (LEC),(SFP+,LC)
hpnicfevtModuleSw-CR-SPC-XP4L-E-I             OBJECT IDENTIFIER ::= { hpnicfevtModuleSwitchType 930 } -- 4-Port 10GBASE-R/W Optical Interface Module,(XFP,LC)
hpnicfevtModuleSw-LST2MRPNC1                  OBJECT IDENTIFIER ::= { hpnicfevtModuleSwitchType 931 } -- Management and Route Process Unit
hpnicfevtModuleSw-LST2SF08C1                  OBJECT IDENTIFIER ::= { hpnicfevtModuleSwitchType 932 } -- Switch Fabric Card
hpnicfevtModuleSw-LST2SF18C1                  OBJECT IDENTIFIER ::= { hpnicfevtModuleSwitchType 933 } -- Switch Fabric Card
hpnicfevtModuleSw-SR02SRP2G3                  OBJECT IDENTIFIER ::= { hpnicfevtModuleSwitchType 934 } -- Routing Switch Processing Board(2G)
hpnicfevtModuleSw-CR-SPE-3020-E-I             OBJECT IDENTIFIER ::= { hpnicfevtModuleSwitchType 935 } -- CR15LN3CNA1, Dual Service Processing Board
hpnicfevtModuleSw-CR-SPC-PUP4L-E-I            OBJECT IDENTIFIER ::= { hpnicfevtModuleSwitchType 936 } -- 4-Port 10G POS Optical Interface Board(Enhanced),(XFP,LC)
hpnicfevtModuleSw-CR-SPC-XP4LEF-I             OBJECT IDENTIFIER ::= { hpnicfevtModuleSwitchType 937 } -- 4-Port 10GBASE-R/W Interface Module (LEF),(XFP,LC)
hpnicfevtModuleSw-CR-SPC-XP8LEF-I             OBJECT IDENTIFIER ::= { hpnicfevtModuleSwitchType 938 } -- 8-Port 10GBASE-R/W Interface Module (LEF),(XFP,LC)
hpnicfevtModuleSw-LST3XP8LEB1                 OBJECT IDENTIFIER ::= { hpnicfevtModuleSwitchType 939 } -- 8-Port 10GBASE-R Interface Module (LEB),(XFP,LC)
hpnicfevtModuleSw-LST3XP8LEC1                 OBJECT IDENTIFIER ::= { hpnicfevtModuleSwitchType 940 } -- 8-Port 10GBASE-R Interface Module (LEC),(XFP,LC)
hpnicfevtModuleSw-LST1FW3A1                   OBJECT IDENTIFIER ::= { hpnicfevtModuleSwitchType 941 } -- Firewall Board
hpnicfevtModuleSw-CR-IM-NAM1A                 OBJECT IDENTIFIER ::= { hpnicfevtModuleSwitchType 942 } -- CR1M1NAM1A1, Network Analysis Service Module, Domestic&Overseas Version
hpnicfevtModuleSw-LSR2SRP2B1                  OBJECT IDENTIFIER ::= { hpnicfevtModuleSwitchType 943 } -- Management and Route Process Unit
hpnicfevtModuleSw-LSR2SRP2B2                  OBJECT IDENTIFIER ::= { hpnicfevtModuleSwitchType 944 } -- Management and Route Process Unit
hpnicfevtModuleSw-LSR2SRP2D1                  OBJECT IDENTIFIER ::= { hpnicfevtModuleSwitchType 945 } -- Management and Route Process Unit
hpnicfevtModuleSw-LST3XP8LEY1                 OBJECT IDENTIFIER ::= { hpnicfevtModuleSwitchType 946 } -- 8-Port 10GBASE-R/W Interface Module (LEY),(XFP,LC)
hpnicfevtModuleSw-LST2XP32REY1                OBJECT IDENTIFIER ::= { hpnicfevtModuleSwitchType 947 } -- 32-Port 10GBASE-R Interface Module(REY),(SFP+,LC)
hpnicfevtModuleSw-LST1XP16LEY1                OBJECT IDENTIFIER ::= { hpnicfevtModuleSwitchType 948 } -- 16-Port 10GBASE-R Interface Module (LEY),(SFP+,LC)
hpnicfevtModuleSw-SR0M2SRP2G3                 OBJECT IDENTIFIER ::= { hpnicfevtModuleSwitchType 949 } -- Routing Switch Processing Board(2G)
hpnicfevtModuleSw-SR0M2SRP1G3                 OBJECT IDENTIFIER ::= { hpnicfevtModuleSwitchType 950 } -- Routing Switch Processing Board(1G)
hpnicfevtModuleSw-SPC-GP48LA                  OBJECT IDENTIFIER ::= { hpnicfevtModuleSwitchType 951 } -- 48-Port 1000BASE-X Interface Service Module,(SFP,LC)
hpnicfevtModuleSw-SPC-GT48LA                  OBJECT IDENTIFIER ::= { hpnicfevtModuleSwitchType 952 } -- 48-Port 10/100/1000BASE-T Interface Service Module,(RJ45)
hpnicfevtModuleSw-SPC-XP4LA                   OBJECT IDENTIFIER ::= { hpnicfevtModuleSwitchType 953 } -- 4-Port 10GBase-R/W Interface Service Module,(XFP,LC)
hpnicfevtModuleSw-SPC-XP2LA                   OBJECT IDENTIFIER ::= { hpnicfevtModuleSwitchType 954 } -- 2-Port 10GBASE-R/W Interface Service Module,(XFP,LC)
hpnicfevtModuleSw-SPC-GP24LA                  OBJECT IDENTIFIER ::= { hpnicfevtModuleSwitchType 955 } -- 16-Port 1000BASE-X Interface(SFP,LC)+8-Port Combo Interface Service Module
hpnicfevtModuleSw-SPC-XP16RA                  OBJECT IDENTIFIER ::= { hpnicfevtModuleSwitchType 956 } -- 16-Port 10GBASE-R Optical Interface Service Module(RA),(SFP+,LC)
hpnicfevtModuleSw-CR-IM-FW1A                  OBJECT IDENTIFIER ::= { hpnicfevtModuleSwitchType 957 } -- Firewall Service Processing Board
hpnicfevtModuleSw-SPC-XP16R                   OBJECT IDENTIFIER ::= { hpnicfevtModuleSwitchType 958 } -- 16-Port 10GBASE-R Optical Interface Service Module(R),(SFP+,LC)
hpnicfevtModuleSw-CR-IM-LB1A                  OBJECT IDENTIFIER ::= { hpnicfevtModuleSwitchType 959 } -- Load Balancing Service Processing Board
hpnicfevtModuleSw-LST1GT48LEC2                OBJECT IDENTIFIER ::= { hpnicfevtModuleSwitchType 960 } -- 48-Port 10/100/1000BASE-T Interface Module(LEC),(RJ45)
hpnicfevtModuleSw-LST1GP48LEC2                OBJECT IDENTIFIER ::= { hpnicfevtModuleSwitchType 961 } -- 48-Port 1000BASE-X Interface Module (LEC),(SFP,LC)
hpnicfevtModuleSw-LST1XP16LEC2                OBJECT IDENTIFIER ::= { hpnicfevtModuleSwitchType 962 } -- 16-Port 10GBASE-R Interface Module (LEC),(SFP+,LC)
hpnicfevtModuleSw-LST2XP8LEC2                 OBJECT IDENTIFIER ::= { hpnicfevtModuleSwitchType 963 } -- 8-Port 10GBASE-R/W Interface Module(LEC),(XFP,LC)
hpnicfevtModuleSw-LST2XP32REC2                OBJECT IDENTIFIER ::= { hpnicfevtModuleSwitchType 964 } -- 32-Port 10GBASE-R Interface Module(REC),(SFP+,LC)
hpnicfevtModuleSw-CR-IM-MAC1A                 OBJECT IDENTIFIER ::= { hpnicfevtModuleSwitchType 965 } -- Master Access Control Service Module
hpnicfevtModuleSw-LST1XP48LFD1                OBJECT IDENTIFIER ::= { hpnicfevtModuleSwitchType 966 } -- 48-Port 10GBASE-R Interface Module (LFD),(SFP+,LC)
hpnicfevtModuleSw-LST1XP40RFD1                OBJECT IDENTIFIER ::= { hpnicfevtModuleSwitchType 967 } -- 40-Port 10GBASE-R Interface Module (RFD),(SFP+,LC)
hpnicfevtModuleSw-LST1XP40RFG1                OBJECT IDENTIFIER ::= { hpnicfevtModuleSwitchType 968 } -- 40-Port 10GBASE-R/W Interface Module (RFG),(SFP+,LC)
hpnicfevtModuleSw-LST1XLP16RFD1               OBJECT IDENTIFIER ::= { hpnicfevtModuleSwitchType 969 } -- 16-Port 40GBASE-R Interface Module (RFD),(QSFP+,LC)
hpnicfevtModuleSw-LST1CP4RFD1                 OBJECT IDENTIFIER ::= { hpnicfevtModuleSwitchType 970 } -- 4-Port 100GBASE-R Interface Module (RFD),(CFP,LC)
hpnicfevtModuleSw-LST1CP4RFG1                 OBJECT IDENTIFIER ::= { hpnicfevtModuleSwitchType 971 } -- 4-Port 100GBASE-R Interface Module (RFG),(CFP,LC)
hpnicfevtModuleSw-LST1SF08E1                  OBJECT IDENTIFIER ::= { hpnicfevtModuleSwitchType 972 } -- Switch Fabric Card
hpnicfevtModuleSw-LST1SF18E1                  OBJECT IDENTIFIER ::= { hpnicfevtModuleSwitchType 973 } -- Switch Fabric Card
hpnicfevtModuleSw-LST1MRPNE1                  OBJECT IDENTIFIER ::= { hpnicfevtModuleSwitchType 974 } -- Management and Route Process Unit
hpnicfevtModuleSw-LSX1CGX8FC0                 OBJECT IDENTIFIER ::= { hpnicfevtModuleSwitchType 975 } -- 8-Port 100GBASE-R Interface Module (FC),(CXP,MPO)
hpnicfevtModuleSw-LSX1CGX8FC1                 OBJECT IDENTIFIER ::= { hpnicfevtModuleSwitchType 976 } -- 8-Port 100GBASE-R Interface Module (FC),(CXP,MPO)
hpnicfevtModuleSw-LSX1QGS24FC0                OBJECT IDENTIFIER ::= { hpnicfevtModuleSwitchType 977 } -- 24-Port 40GBASE-R Interface Module (FC),(QSFP+)
hpnicfevtModuleSw-LSX1QGS24FC1                OBJECT IDENTIFIER ::= { hpnicfevtModuleSwitchType 978 } -- 24-Port 40GBASE-R Interface Module (FC),(QSFP+)
hpnicfevtModuleSw-LSX1TGS24FC0                OBJECT IDENTIFIER ::= { hpnicfevtModuleSwitchType 979 } -- 24-Port 10GBASE-R Interface Module (FC),(SFP+,LC)
hpnicfevtModuleSw-LSX1TGS24FC1                OBJECT IDENTIFIER ::= { hpnicfevtModuleSwitchType 980 } -- 24-Port 10GBASE-R Interface Module (FC),(SFP+,LC)
hpnicfevtModuleSw-LSX1TGS48FC0                OBJECT IDENTIFIER ::= { hpnicfevtModuleSwitchType 981 } -- 48-Port 10GBASE-R Interface Module (FC),(SFP+,LC)
hpnicfevtModuleSw-LSX1TGS48FC1                OBJECT IDENTIFIER ::= { hpnicfevtModuleSwitchType 982 } -- 48-Port 10GBASE-R Interface Module (FC),(SFP+,LC)
hpnicfevtModuleSw-LST1XP48LFD2                OBJECT IDENTIFIER ::= { hpnicfevtModuleSwitchType 983 } -- 48-Port 10GBASE-R Interface Module (LFD),(SFP+,LC)
hpnicfevtModuleSw-LST1XP40RFD2                OBJECT IDENTIFIER ::= { hpnicfevtModuleSwitchType 984 } -- 40-Port 10GBASE-R Interface Module (RFD),(SFP+,LC)
hpnicfevtModuleSw-LST1XP40RFG2                OBJECT IDENTIFIER ::= { hpnicfevtModuleSwitchType 985 } -- 40-Port 10GBASE-R/W Interface Module (RFG),(SFP+,LC)
hpnicfevtModuleSw-LST1XLP16RFD2               OBJECT IDENTIFIER ::= { hpnicfevtModuleSwitchType 986 } -- 16-Port 40GBASE-R Interface Module (RFD),(QSFP+)
hpnicfevtModuleSw-LST1CP4RFD2                 OBJECT IDENTIFIER ::= { hpnicfevtModuleSwitchType 987 } -- 4-Port 100GBASE-R Interface Module (RFD),(CFP)
hpnicfevtModuleSw-LST1CP4RFG2                 OBJECT IDENTIFIER ::= { hpnicfevtModuleSwitchType 988 } -- 4-Port 100GBASE-R Interface Module (RFG),(CFP)
hpnicfevtModuleSw-MPE-1004                    OBJECT IDENTIFIER ::= { hpnicfevtModuleSwitchType 989 } -- Multi-Service Processing Engine
hpnicfevtModuleSw-MIC-GP4L                    OBJECT IDENTIFIER ::= { hpnicfevtModuleSwitchType 990 } -- 4-Port 1000BASE-X COMBO Interface Card,(SFP,LC)
hpnicfevtModuleSw-MIC-GP8L                    OBJECT IDENTIFIER ::= { hpnicfevtModuleSwitchType 991 } -- 8-Port 1000BASE-X Optical Interface Card,(SFP,LC)
hpnicfevtModuleSw-MIC-SP4L                    OBJECT IDENTIFIER ::= { hpnicfevtModuleSwitchType 992 } -- 4-Port OC-3/STM-1 POS/CPOS/ATM or 1-Port OC-12/STM-4 POS/ATM Optical Interface Card,(SFP,LC)
hpnicfevtModuleSw-MIC-ET16L                   OBJECT IDENTIFIER ::= { hpnicfevtModuleSwitchType 993 } -- 16-Port E1/T1 Electrical Interface Card
hpnicfevtModuleSw-MIC-CLP4L                   OBJECT IDENTIFIER ::= { hpnicfevtModuleSwitchType 994 } -- 4-Port OC-3/STM-1 CPOS/POS Optical Interface Card,(SFP,LC)
hpnicfevtModuleSw-MIC-CLP2L                   OBJECT IDENTIFIER ::= { hpnicfevtModuleSwitchType 995 } -- 2-Port OC-3/STM-1 CPOS/POS Optical Interface Card,(SFP,LC)
hpnicfevtModuleSw-LST1IPS2A1                  OBJECT IDENTIFIER ::= { hpnicfevtModuleSwitchType 996 } -- Intrusion Prevention System Module
hpnicfevtModuleSw-SFC-04B                     OBJECT IDENTIFIER ::= { hpnicfevtModuleSwitchType 997 } -- Switch Fabric Card(B Type)
hpnicfevtModuleSw-SFC-04D                     OBJECT IDENTIFIER ::= { hpnicfevtModuleSwitchType 998 } -- Switch Fabric Card(D Type)
hpnicfevtModuleSw-SFC-08B                     OBJECT IDENTIFIER ::= { hpnicfevtModuleSwitchType 999 } -- Switch Fabric Card(B Type)
hpnicfevtModuleSw-SFC-08D                     OBJECT IDENTIFIER ::= { hpnicfevtModuleSwitchType 1000 } -- Switch Fabric Card(D Type)
hpnicfevtModuleSw-SFC-12B                     OBJECT IDENTIFIER ::= { hpnicfevtModuleSwitchType 1001 } -- Switch Fabric Card(B Type)
hpnicfevtModuleSw-SFC-12D                     OBJECT IDENTIFIER ::= { hpnicfevtModuleSwitchType 1002 } -- Switch Fabric Card(D Type)
hpnicfevtModuleSw-SR05SRP1H1                  OBJECT IDENTIFIER ::= { hpnicfevtModuleSwitchType 1003 } -- Routing Switch Processing Unit(1H)
hpnicfevtModuleSw-SPC-GP24LA1                 OBJECT IDENTIFIER ::= { hpnicfevtModuleSwitchType 1004 } -- 16-Port 1000BASE-X Ethernet Optical Interface(SFP,LC)+8-Port Combo Interface Module(A Type)
hpnicfevtModuleSw-SPC-GP24XP2LA               OBJECT IDENTIFIER ::= { hpnicfevtModuleSwitchType 1005 } -- 16-Port 1000BASE-X Ethernet Optical Interface(SFP,LC)+8-Port Combo Interface+2-Port 10GE Optical Interface Module(XFP,LC)(A Type)
hpnicfevtModuleSw-SPC-GP48LA1                 OBJECT IDENTIFIER ::= { hpnicfevtModuleSwitchType 1006 } -- 48-Port 1000BASE-X Ethernet Optical Interface Module(SFP,LC)(A Type)
hpnicfevtModuleSw-SPC-GP48LB                  OBJECT IDENTIFIER ::= { hpnicfevtModuleSwitchType 1007 } -- 48-Port Enhanced 1000BASE-X Ethernet Optical Interface Module(SFP,LC)(B Type)
hpnicfevtModuleSw-SPC-XP2LA1                  OBJECT IDENTIFIER ::= { hpnicfevtModuleSwitchType 1008 } -- 2-Port 10GBASE Ethernet Optical Interface Module(XFP,LC)(A Type)
hpnicfevtModuleSw-SPC-XP4LA1                  OBJECT IDENTIFIER ::= { hpnicfevtModuleSwitchType 1009 } -- 4-Port 10GBASE Ethernet Optical Interface Module(XFP,LC)(A Type)
hpnicfevtModuleSw-SPC-XP4LB                   OBJECT IDENTIFIER ::= { hpnicfevtModuleSwitchType 1010 } -- 4-Port Enhanced 10GBASE Ethernet Optical Interface Module(XFP,LC)(A Type)
hpnicfevtModuleSw-SPC-XP8LA                   OBJECT IDENTIFIER ::= { hpnicfevtModuleSwitchType 1011 } -- 8-Port 10GBASE Ethernet Optical Interface Module(SFP+,LC)(A Type)
hpnicfevtModuleSw-SPC-XP8LB                   OBJECT IDENTIFIER ::= { hpnicfevtModuleSwitchType 1012 } -- 8-Port Enhanced 10GBASE Ethernet Optical Interface Module(SFP+,LC)(B Type)
hpnicfevtModuleSw-SPC-XP48LA                  OBJECT IDENTIFIER ::= { hpnicfevtModuleSwitchType 1013 } -- 48-Port 10GBASE Ethernet Optical Interface Module(SFP+,LC)(A Type)
hpnicfevtModuleSw-SPC-XLP8LA                  OBJECT IDENTIFIER ::= { hpnicfevtModuleSwitchType 1014 } -- 8-Port 40GBASE Ethernet Optical Interface Module(QSFP+,MPO)(A Type)
hpnicfevtModuleSw-SPC-GP24XP2LB               OBJECT IDENTIFIER ::= { hpnicfevtModuleSwitchType 1015 } -- 16-Port 1000BASE-X Optical Interface(SFP,LC)+8-Port Combo Interface+2-Port 10GE Optical Interface Module(XFP,LC)(B Type)
hpnicfevtModuleSw-LST1MRPNE2                  OBJECT IDENTIFIER ::= { hpnicfevtModuleSwitchType 1016 } -- Management and Route Process Unit
hpnicfevtModuleSw-LST2FW3A1                   OBJECT IDENTIFIER ::= { hpnicfevtModuleSwitchType 1017 } -- Firewall Board
hpnicfevtModuleSw-LST1ADE1A1                  OBJECT IDENTIFIER ::= { hpnicfevtModuleSwitchType 1018 } -- Load Balancing Board
hpnicfevtModuleSw-CR-MRP-II                   OBJECT IDENTIFIER ::= { hpnicfevtModuleSwitchType 1019 } -- Management and Route Unit-II
hpnicfevtModuleSw-CR-SF08E                    OBJECT IDENTIFIER ::= { hpnicfevtModuleSwitchType 1020 } -- Switch Fabric Module(E)
hpnicfevtModuleSw-CR-SF18E                    OBJECT IDENTIFIER ::= { hpnicfevtModuleSwitchType 1021 } -- Switch Fabric Module(E)
hpnicfevtModuleSw-CR-SPC-XP40RC               OBJECT IDENTIFIER ::= { hpnicfevtModuleSwitchType 1022 } -- 40-Port 10GBASE-R/W Optical Interface Module(RC),(SFP+,LC)
hpnicfevtModuleSw-CR-SPC-XP40RB               OBJECT IDENTIFIER ::= { hpnicfevtModuleSwitchType 1023 } -- 40-Port 10GBASE-R Ethernet Optical Interface Module(RB),(SFP+,LC)
hpnicfevtModuleSw-CR-SPC-CP4RC                OBJECT IDENTIFIER ::= { hpnicfevtModuleSwitchType 1024 } -- 4-Port 100GBASE Ethernet Optical Interface Module(RC),(CFP)
hpnicfevtModuleSw-LST1FW3C1                   OBJECT IDENTIFIER ::= { hpnicfevtModuleSwitchType 1025 } -- Firewall Board
hpnicfevtModuleSw-LSU1FWCEA0                  OBJECT IDENTIFIER ::= { hpnicfevtModuleSwitchType 1026 } -- Firewall Board
hpnicfevtModuleSw-SPC-GT48LA1                 OBJECT IDENTIFIER ::= { hpnicfevtModuleSwitchType 1027 } -- 48-Port 10/100/1000BASE-T Ethernet Interface Module(RJ45)(A Type)
hpnicfevtModuleSw-LST1XP20RFD1                OBJECT IDENTIFIER ::= { hpnicfevtModuleSwitchType 1028 } -- 20-Port 10GBASE-R Interface Module (RFD),(SFP+,LC)
hpnicfevtModuleSw-LST1XP20RFD2                OBJECT IDENTIFIER ::= { hpnicfevtModuleSwitchType 1029 } -- 20-Port 10GBASE-R Interface Module (RFD),(SFP+,LC)
hpnicfevtModuleSw-MPE-1104                    OBJECT IDENTIFIER ::= { hpnicfevtModuleSwitchType 1030 } -- 4-Port Multiservice Processing Engine
hpnicfevtModuleSw-SPEX-1204                   OBJECT IDENTIFIER ::= { hpnicfevtModuleSwitchType 1031 } -- 4-Port 10G Processing Engine
hpnicfevtModuleSw-SPC-GP44XP4LCX              OBJECT IDENTIFIER ::= { hpnicfevtModuleSwitchType 1032 } -- 44-Port 100/1000BASE-X Ethernet Optical Interface Module(SFP,LC)+4-Port 10GBASE Ethernet Optical Interface Module(SFP+,LC)(C Type)
hpnicfevtModuleSw-SPC-GP44XP4LAX              OBJECT IDENTIFIER ::= { hpnicfevtModuleSwitchType 1033 } -- 44-Port 100/1000BASE-X Ethernet Optical Interface Module(SFP,LC)+4-Port 10GBASE Ethernet Optical Interface Module(SFP+,LC)(A Type)
hpnicfevtModuleSw-SPC-XP24LCX                 OBJECT IDENTIFIER ::= { hpnicfevtModuleSwitchType 1034 } -- 24-Port 10GBASE Ethernet Optical Interface Module(SFP+,LC)(C Type)
hpnicfevtModuleSw-SPC-XP24LAX                 OBJECT IDENTIFIER ::= { hpnicfevtModuleSwitchType 1035 } -- 24-Port 10GBASE Ethernet Optical Interface Module(SFP+,LC)(A Type)
hpnicfevtModuleSw-SPC-XP12LCX                 OBJECT IDENTIFIER ::= { hpnicfevtModuleSwitchType 1036 } -- 12-Port 10GBASE Ethernet Optical Interface Module(SFP+,LC)(C Type)
hpnicfevtModuleSw-SPC-XP12LAX                 OBJECT IDENTIFIER ::= { hpnicfevtModuleSwitchType 1037 } -- 12-Port 10GBASE Ethernet Optical Interface Module(SFP+,LC)(A Type)
hpnicfevtModuleSw-SPC-XLP6LCX                 OBJECT IDENTIFIER ::= { hpnicfevtModuleSwitchType 1038 } -- 6-Port 40GBASE Ethernet Optical Interface Module(QSFP+,MPO)(C Type)
hpnicfevtModuleSw-SPC-XLP6LAX                 OBJECT IDENTIFIER ::= { hpnicfevtModuleSwitchType 1039 } -- 6-Port 40GBASE Ethernet Optical Interface Module(QSFP+,MPO)(A Type)
hpnicfevtModuleSw-SPC-CP1LCX                  OBJECT IDENTIFIER ::= { hpnicfevtModuleSwitchType 1040 } -- 1-Port 100GBASE Ethernet Optical Interface Module(CFP,LC)(C Type)
hpnicfevtModuleSw-SPC-CP1LAX                  OBJECT IDENTIFIER ::= { hpnicfevtModuleSwitchType 1041 } -- 1-Port 100GBASE Ethernet Optical Interface Module(CFP,LC)(A Type)
hpnicfevtModuleSw-SPC-CP2LB                   OBJECT IDENTIFIER ::= { hpnicfevtModuleSwitchType 1042 } -- 2-Port 100GBASE Ethernet Optical Interface Module(CFP,LC)(B Type)
hpnicfevtModuleSw-SPC-CP2LA                   OBJECT IDENTIFIER ::= { hpnicfevtModuleSwitchType 1043 } -- 2-Port 100GBASE Ethernet Optical Interface Module(CFP,LC)(A Type)
hpnicfevtModuleSw-SR05SRP1L1                  OBJECT IDENTIFIER ::= { hpnicfevtModuleSwitchType 1044 } -- Management and Route Process Unit(1L1)
hpnicfevtModuleSw-SR05SRP1L3                  OBJECT IDENTIFIER ::= { hpnicfevtModuleSwitchType 1045 } -- Management and Route Process Unit(1L3)
hpnicfevtModuleSw-SFC-04-4                    OBJECT IDENTIFIER ::= { hpnicfevtModuleSwitchType 1046 } -- Short-circuit Card Slot 4
hpnicfevtModuleSw-SFC-04-3                    OBJECT IDENTIFIER ::= { hpnicfevtModuleSwitchType 1047 } -- Short-circuit Card Slot 3
hpnicfevtModuleSw-SFC-04-2                    OBJECT IDENTIFIER ::= { hpnicfevtModuleSwitchType 1048 } -- Short-circuit Card Slot 2
hpnicfevtModuleSw-SFC-04-1                    OBJECT IDENTIFIER ::= { hpnicfevtModuleSwitchType 1049 } -- Short-circuit Card Slot 1
hpnicfevtModuleSw-LST1NSM2C1                  OBJECT IDENTIFIER ::= { hpnicfevtModuleSwitchType 1050 } -- NetStream Service Board
hpnicfevtModuleSw-CR-SPC-XP20RB               OBJECT IDENTIFIER ::= { hpnicfevtModuleSwitchType 1051 } -- 20-Port 10GBASE-R Ethernet Optical Interface Module(RB),(SFP+,LC)
hpnicfevtModuleSw-SR07SRPUA1                  OBJECT IDENTIFIER ::= { hpnicfevtModuleSwitchType 1052 } -- Management and Route Process Unit(UA1)
hpnicfevtModuleSw-SR07SRPUB3                  OBJECT IDENTIFIER ::= { hpnicfevtModuleSwitchType 1053 } -- Management and Route Process Unit(UB1)
hpnicfevtModuleSw-SR07SRPUC3                  OBJECT IDENTIFIER ::= { hpnicfevtModuleSwitchType 1054 } -- Management and Route Process Unit
hpnicfevtModuleSw-SR07MPUA1                   OBJECT IDENTIFIER ::= { hpnicfevtModuleSwitchType 1055 } -- Management and Route Process Unit
hpnicfevtModuleSw-SR07SRPUB1                  OBJECT IDENTIFIER ::= { hpnicfevtModuleSwitchType 1056 } -- Management and Route Process Unit(UB1)
hpnicfevtModuleSw-SR07SRPUC1                  OBJECT IDENTIFIER ::= { hpnicfevtModuleSwitchType 1057 } -- Management and Route Process Unit
hpnicfevtModuleSw-MIC-MS4L                    OBJECT IDENTIFIER ::= { hpnicfevtModuleSwitchType 1058 } -- 4-Port Multi-Service Optical Interface Card,Domestic&Overseas Version
hpnicfevtModuleSw-SPC-GP44XP4LC               OBJECT IDENTIFIER ::= { hpnicfevtModuleSwitchType 1059 } -- 44-Port 100/1000BASE-X Ethernet Optical Interface Board(SFP,LC)+4-Port 10GBASE Ethernet Optical Interface Board(SFP+,LC)(C Type)
hpnicfevtModuleSw-SPC-GP44XP4LA               OBJECT IDENTIFIER ::= { hpnicfevtModuleSwitchType 1060 } -- 44-Port 100/1000BASE-X Ethernet Optical Interface Board(SFP,LC)+4-Port 10GBASE Ethernet Optical Interface Board(SFP+,LC)(A Type)
hpnicfevtModuleSw-SPC-XLP2XP4LC               OBJECT IDENTIFIER ::= { hpnicfevtModuleSwitchType 1061 } -- 2-Port 40GBASE Ethernet Optical Interface Board(QSFP+,MPO)+4-Port 10GBASE Ethernet Optical Interface Board(SFP+,LC)(C Type)
hpnicfevtModuleSw-SPC-XP12LC                  OBJECT IDENTIFIER ::= { hpnicfevtModuleSwitchType 1062 } -- 12-Port 10GBASE Ethernet Optical Interface Board(SFP+,LC)(C Type)
hpnicfevtModuleSw-SPC-CP1LC                   OBJECT IDENTIFIER ::= { hpnicfevtModuleSwitchType 1063 } -- 1-Port 100GBASE Ethernet Optical Interface Module(CFP,LC)(C Type)
hpnicfevtModuleSw-SPC-XP24LC                  OBJECT IDENTIFIER ::= { hpnicfevtModuleSwitchType 1064 } -- 24-Port 10GBASE Ethernet Optical Interface Board(SFP+,LC)(C Type)
hpnicfevtModuleSw-SR07SRPUD3                  OBJECT IDENTIFIER ::= { hpnicfevtModuleSwitchType 1065 } -- Management and Route Process Unit(UD1)
hpnicfevtModuleSw-SR07MPUA3                   OBJECT IDENTIFIER ::= { hpnicfevtModuleSwitchType 1066 } -- Management and Route Process Unit(For 02 Chassis)
hpnicfevtModuleSw-MPEX-1304                   OBJECT IDENTIFIER ::= { hpnicfevtModuleSwitchType 1067 } -- 4-Port Multiservice Processing Engine
hpnicfevtModuleSw-MIC-GP10L1                  OBJECT IDENTIFIER ::= { hpnicfevtModuleSwitchType 1068 } -- 6-Port 1000BASE-X Optical Interface Card(SFP,LC)+4-Port 1000BASE-X/10GBASE Optical Interface Card(SFP+,LC)
hpnicfevtModuleSw-SR07SRPUB                   OBJECT IDENTIFIER ::= { hpnicfevtModuleSwitchType 1069 } -- Management and Route Processing Unit(UB3)
hpnicfevtModuleSw-CMPE-1104                   OBJECT IDENTIFIER ::= { hpnicfevtModuleSwitchType 1070 } -- 4-Port Multiservice Processing Engine
hpnicfevtModuleSw-CSFC-04-1                   OBJECT IDENTIFIER ::= { hpnicfevtModuleSwitchType 1071 } -- Fabric Card Slot 1
hpnicfevtModuleSw-CSFC-04-2                   OBJECT IDENTIFIER ::= { hpnicfevtModuleSwitchType 1072 } -- Fabric Card Slot 2
hpnicfevtModuleSw-CSFC-04-3                   OBJECT IDENTIFIER ::= { hpnicfevtModuleSwitchType 1073 } -- Fabric Card Slot 3
hpnicfevtModuleSw-CSFC-04-4                   OBJECT IDENTIFIER ::= { hpnicfevtModuleSwitchType 1074 } -- Fabric Card Slot 4
hpnicfevtModuleSw-CSFC-04B                    OBJECT IDENTIFIER ::= { hpnicfevtModuleSwitchType 1075 } -- Switch Fabric Card(B Type)
hpnicfevtModuleSw-CSFC-04D                    OBJECT IDENTIFIER ::= { hpnicfevtModuleSwitchType 1076 } -- Switch Fabric Card(D Type)
hpnicfevtModuleSw-CSFC-08B                    OBJECT IDENTIFIER ::= { hpnicfevtModuleSwitchType 1077 } -- Switch Fabric Card(B Type)
hpnicfevtModuleSw-CSFC-08D                    OBJECT IDENTIFIER ::= { hpnicfevtModuleSwitchType 1078 } -- Switch Fabric Card(D Type)
hpnicfevtModuleSw-CSFC-12B                    OBJECT IDENTIFIER ::= { hpnicfevtModuleSwitchType 1079 } -- Switch Fabric Card(B Type)
hpnicfevtModuleSw-CSFC-12D                    OBJECT IDENTIFIER ::= { hpnicfevtModuleSwitchType 1080 } -- Switch Fabric Card(D Type)
hpnicfevtModuleSw-CSPC-CP1LCX                 OBJECT IDENTIFIER ::= { hpnicfevtModuleSwitchType 1081 } -- 1-Port 100GBASE Ethernet Optical Interface Module(CFP,LC)(C Type)
hpnicfevtModuleSw-CSPC-CP2LB                  OBJECT IDENTIFIER ::= { hpnicfevtModuleSwitchType 1082 } -- 2-Port 100GBASE Ethernet Optical Interface Module(CFP,LC)(B Type)
hpnicfevtModuleSw-CSPC-GP24LA1                OBJECT IDENTIFIER ::= { hpnicfevtModuleSwitchType 1083 } -- 16-Port 1000BASE-X Ethernet Optical Interface(SFP,LC)+8-Port Combo Interface Module(A Type)
hpnicfevtModuleSw-CSPC-GP24XP2LB              OBJECT IDENTIFIER ::= { hpnicfevtModuleSwitchType 1084 } -- 16-Port 1000BASE-X Optical Interface(SFP,LC)+8-Port Combo Interface+2-Port 10GE Optical Interface Module(XFP,LC)(B Type)
hpnicfevtModuleSw-CSPC-GP44XP4LCX             OBJECT IDENTIFIER ::= { hpnicfevtModuleSwitchType 1085 } -- 44-Port 1000BASE-X Ethernet Optical Interface Module(SFP,LC)+4-Port 10GBASE Ethernet Optical Interface Module(SFP+,LC)(C Type)
hpnicfevtModuleSw-CSPC-GP48LB                 OBJECT IDENTIFIER ::= { hpnicfevtModuleSwitchType 1086 } -- 48-Port Enhanced 1000BASE-X Ethernet Optical Interface Module(SFP,LC)(B Type)
hpnicfevtModuleSw-CSPC-GT48LA1                OBJECT IDENTIFIER ::= { hpnicfevtModuleSwitchType 1087 } -- 48-Port 10/100/1000BASE-T Ethernet Interface Module(RJ45)(A Type)
hpnicfevtModuleSw-CSPC-XLP6LCX                OBJECT IDENTIFIER ::= { hpnicfevtModuleSwitchType 1088 } -- 6-Port 40GBASE Ethernet Optical Interface Module(QSFP+,MPO)(C Type)
hpnicfevtModuleSw-CSPC-XP2LA1                 OBJECT IDENTIFIER ::= { hpnicfevtModuleSwitchType 1089 } -- 2-Port 10GBASE Ethernet Optical Interface Module(XFP,LC)(A Type)
hpnicfevtModuleSw-CSPC-XP4LB                  OBJECT IDENTIFIER ::= { hpnicfevtModuleSwitchType 1090 } -- 4-Port Enhanced 10GBASE Ethernet Optical Interface Module(XFP,LC)(B Type)
hpnicfevtModuleSw-CSPC-XP8LB                  OBJECT IDENTIFIER ::= { hpnicfevtModuleSwitchType 1091 } -- 8-Port Enhanced 10GBASE Ethernet Optical Interface Module(SFP+,LC)(B Type)
hpnicfevtModuleSw-CSPC-XP12LAX                OBJECT IDENTIFIER ::= { hpnicfevtModuleSwitchType 1092 } -- 12-Port 10GBASE Ethernet Optical Interface Module(SFP+,LC)(A Type)
hpnicfevtModuleSw-CSPC-XP12LCX                OBJECT IDENTIFIER ::= { hpnicfevtModuleSwitchType 1093 } -- 12-Port 10GBASE Ethernet Optical Interface Module(SFP+,LC)(C Type)
hpnicfevtModuleSw-CSPC-XP24LAX                OBJECT IDENTIFIER ::= { hpnicfevtModuleSwitchType 1094 } -- 24-Port 10GBASE Ethernet Optical Interface Module(SFP+,LC)(A Type)
hpnicfevtModuleSw-CSPC-XP24LCX                OBJECT IDENTIFIER ::= { hpnicfevtModuleSwitchType 1095 } -- 24-Port 10GBASE Ethernet Optical Interface Module(SFP+,LC)(C Type)
hpnicfevtModuleSw-CSPC-CSPEX-1204             OBJECT IDENTIFIER ::= { hpnicfevtModuleSwitchType 1096 } -- 4-Port 10G Processing Engine
hpnicfevtModuleSw-CSR05SRP1L1                 OBJECT IDENTIFIER ::= { hpnicfevtModuleSwitchType 1097 } -- Management and Route Process Unit(1L1)
hpnicfevtModuleSw-CSR05SRP1L3                 OBJECT IDENTIFIER ::= { hpnicfevtModuleSwitchType 1098 } -- Management and Route Process Unit(1L3)
hpnicfevtModuleSw-CSR07MPUA1                  OBJECT IDENTIFIER ::= { hpnicfevtModuleSwitchType 1099 } -- Management and Route Processing Unit
hpnicfevtModuleSw-CSR07SRPUA1                 OBJECT IDENTIFIER ::= { hpnicfevtModuleSwitchType 1100 } -- Management and Route Processing Unit(UA1)
hpnicfevtModuleSw-CSR07SRPUB1                 OBJECT IDENTIFIER ::= { hpnicfevtModuleSwitchType 1101 } -- Management and Route Processing Unit(UB1)
hpnicfevtModuleSw-CSR07SRPUC1                 OBJECT IDENTIFIER ::= { hpnicfevtModuleSwitchType 1102 } -- Management and Route Processing Unit
hpnicfevtModuleSw-LSXM1CGX8FX1                OBJECT IDENTIFIER ::= { hpnicfevtModuleSwitchType 1103 } -- 8-Port 100GBASE Ethernet Optical Interface Module(CXP)(FX)
hpnicfevtModuleSw-LSXM1QGS24FX1               OBJECT IDENTIFIER ::= { hpnicfevtModuleSwitchType 1104 } -- 24-Port 40GBASE Ethernet Optical Interface Module(QSFP+)(FX)
hpnicfevtModuleSw-LSXM1TGS48FX1               OBJECT IDENTIFIER ::= { hpnicfevtModuleSwitchType 1105 } -- 48-Port 10GBASE Ethernet Optical Interface Module(SFP+,LC)(FX)
hpnicfevtModuleSw-LSXM1QGS12FX1               OBJECT IDENTIFIER ::= { hpnicfevtModuleSwitchType 1106 } -- 12-Port 40GBASE Ethernet Optical Interface Module(QSFP+)(FX)
hpnicfevtModuleSw-LSXM1TGT48FX1               OBJECT IDENTIFIER ::= { hpnicfevtModuleSwitchType 1107 } -- 48-Port 10GBASE-T Ethernet Electrical Interface Module(RJ45)(FX)
hpnicfevtModuleSw-LSU1IPSBEA0                 OBJECT IDENTIFIER ::= { hpnicfevtModuleSwitchType 1108 } -- Intrusion Prevention System Module

--
-- 1200 to 1399 reserved for secondary switches part II
--
hpnicfevtModuleSw-LSU1QGC4SF0                 OBJECT IDENTIFIER ::= { hpnicfevtModuleSwitchType 1201 } -- 4 Port 40G BASE Ethernet Optical Interface Board(CFP,SC)(SF)
hpnicfevtModuleSw-LSU1QGS8SF0                 OBJECT IDENTIFIER ::= { hpnicfevtModuleSwitchType 1202 } -- 8-Port 40G BASE Ethernet Optical Interface Board(QSFP,MPO)(SF)
hpnicfevtModuleSw-LSU1TGS48SF0                OBJECT IDENTIFIER ::= { hpnicfevtModuleSwitchType 1203 } -- 48-Port 10GBASE Ethernet SFP+ Optical Interface Board
hpnicfevtModuleSw-LSU1QGS4SF0                 OBJECT IDENTIFIER ::= { hpnicfevtModuleSwitchType 1204 } -- 4-Port 40G BASE Ethernet Optical Interface Board(QSFP,MPO)(SF)
hpnicfevtModuleSw-LSU1TGS32SF0                OBJECT IDENTIFIER ::= { hpnicfevtModuleSwitchType 1205 } -- 32-Port 10GBASE Ethernet SFP+ Optical Interface Board
hpnicfevtModuleSw-LSU1FAB08D0                 OBJECT IDENTIFIER ::= { hpnicfevtModuleSwitchType 1206 } -- Switching Fabric Module
hpnicfevtModuleSw-LSU1FAB04B0                 OBJECT IDENTIFIER ::= { hpnicfevtModuleSwitchType 1207 } -- Switching Fabric Module
hpnicfevtModuleSw-LSU1FAB08B0                 OBJECT IDENTIFIER ::= { hpnicfevtModuleSwitchType 1208 } -- Switching Fabric Module
hpnicfevtModuleSw-LSU1FAB12D0                 OBJECT IDENTIFIER ::= { hpnicfevtModuleSwitchType 1209 } -- Switching Fabric Module
hpnicfevtModuleSw-LSU1FAB12B0                 OBJECT IDENTIFIER ::= { hpnicfevtModuleSwitchType 1210 } -- Switching Fabric Module
hpnicfevtModuleSw-LSU1FAB04D0                 OBJECT IDENTIFIER ::= { hpnicfevtModuleSwitchType 1211 } -- Switching Fabric Module
hpnicfevtModuleSw-LSQ1CTGS16SC0               OBJECT IDENTIFIER ::= { hpnicfevtModuleSwitchType 1212 } -- Supervisor Engine Board With 16-Port 10GBASE Ethernet SFP+ Optical Interfaces
hpnicfevtModuleSw-EWPX2CTGS16SC0              OBJECT IDENTIFIER ::= { hpnicfevtModuleSwitchType 1213 } -- Supervisor Engine Board With 16-Port 10GBASE Ethernet SFP+ Optical Interfaces
hpnicfevtModuleSw-LSU3WCMD0                   OBJECT IDENTIFIER ::= { hpnicfevtModuleSwitchType 1214 } -- Access Controller Card
hpnicfevtModuleSw-EWPX3WCMD0                  OBJECT IDENTIFIER ::= { hpnicfevtModuleSwitchType 1215 } -- Access Controller Card
hpnicfevtModuleSw-LSQ1QGS4SC0                 OBJECT IDENTIFIER ::= { hpnicfevtModuleSwitchType 1216 } -- 4-Port 40G BASE Ethernet Optical Interface Board(QSFP+,MPO)(SC)
hpnicfevtModuleSw-LSQ1QGC4SC0                 OBJECT IDENTIFIER ::= { hpnicfevtModuleSwitchType 1217 } -- 4 Port 40GBASE Ethernet Optical Interface Board(CFP)(SC)
hpnicfevtModuleSw-LSU1TGT24SF0                OBJECT IDENTIFIER ::= { hpnicfevtModuleSwitchType 1218 } -- 24-Port 10GBASE-T Ethernet Electrical Interface Board(RJ45)(SF)
hpnicfevtModuleSw-LSQ1QGS8SC3                 OBJECT IDENTIFIER ::= { hpnicfevtModuleSwitchType 1219 } -- 8-Port 40G BASE Ethernet Optical Interface Board(QSFP+,MPO)
hpnicfevtModuleSw-LSQ1TGS32SC3                OBJECT IDENTIFIER ::= { hpnicfevtModuleSwitchType 1220 } -- 32-Port 10GBASE Ethernet SFP+ Optical Interface Board
hpnicfevtModuleSw-LSQ1QGS4SC3                 OBJECT IDENTIFIER ::= { hpnicfevtModuleSwitchType 1221 } -- 4-Port 40GBASE Ethernet Optical Interface Board(QSFP+,MPO)(SC)
hpnicfevtModuleSw-LSQ1TGS48SC3                OBJECT IDENTIFIER ::= { hpnicfevtModuleSwitchType 1222 } -- 48-Port 10GBASE Ethernet SFP+ Optical Interface Board
hpnicfevtModuleSw-LSQ1QGC4SC3                 OBJECT IDENTIFIER ::= { hpnicfevtModuleSwitchType 1223 } -- 4-Port 40GBASE Ethernet Optical Interface Board(CFP)(SC)
hpnicfevtModuleSw-LSQ1FAB12D3                 OBJECT IDENTIFIER ::= { hpnicfevtModuleSwitchType 1224 } -- Switch Fabric Board
hpnicfevtModuleSw-LSQ1FAB08D3                 OBJECT IDENTIFIER ::= { hpnicfevtModuleSwitchType 1225 } -- Switching Fabric Module
hpnicfevtModuleSw-LSQ1FAB04D3                 OBJECT IDENTIFIER ::= { hpnicfevtModuleSwitchType 1226 } -- Switching Fabric Module
hpnicfevtModuleSw-LSQ1TGS8EB3                 OBJECT IDENTIFIER ::= { hpnicfevtModuleSwitchType 1227 } -- 8-Port 10GBASE Ethernet SFP+ Optical Interface Board
hpnicfevtModuleSw-LSQ1TGT24SC3                OBJECT IDENTIFIER ::= { hpnicfevtModuleSwitchType 1228 } -- 24-Port 10GBASE-T Ethernet Electrical Interface Board(RJ45)(SC)
hpnicfevtModuleSw-LSQ1FAB08B0                 OBJECT IDENTIFIER ::= { hpnicfevtModuleSwitchType 1229 } -- Switching Fabric Module
hpnicfevtModuleSw-EWPX2CTGS16SC               OBJECT IDENTIFIER ::= { hpnicfevtModuleSwitchType 1230 } -- Supervisor Engine Board With 16-Port 10GBASE Ethernet SFP+ Optical Interfaces
hpnicfevtModuleSw-LSU1SUPB0                   OBJECT IDENTIFIER ::= { hpnicfevtModuleSwitchType 1231 } -- Supervisor Engine Board
hpnicfevtModuleSw-LSQ1GP48SA0                 OBJECT IDENTIFIER ::= { hpnicfevtModuleSwitchType 1232 } -- 48-Port 1000BASE-X Ethernet Optical Interface Board(SFP,LC)
hpnicfevtModuleSw-LSQ1TGX2SA0                 OBJECT IDENTIFIER ::= { hpnicfevtModuleSwitchType 1233 } -- 2-Port 10GBASE Ethernet Optical Interface Board(XFP,LC)
hpnicfevtModuleSw-LSV1SRPUA1                  OBJECT IDENTIFIER ::= { hpnicfevtModuleSwitchType 1234 } -- Supervisor Engine Board
hpnicfevtModuleSw-LSV1QGS12SA1                OBJECT IDENTIFIER ::= { hpnicfevtModuleSwitchType 1235 } -- 12-Port 40G BASE Ethernet Optical Interface Board(QSFP+)
hpnicfevtModuleSw-LSV1MPUA1                   OBJECT IDENTIFIER ::= { hpnicfevtModuleSwitchType 1236 } -- Supervisor Engine Board
hpnicfevtModuleSw-LSX1SUP10A0                 OBJECT IDENTIFIER ::= { hpnicfevtModuleSwitchType 1237 } -- Supervisor Engine Board
hpnicfevtModuleSw-LSX1SUP16A0                 OBJECT IDENTIFIER ::= { hpnicfevtModuleSwitchType 1238 } -- Supervisor Engine Board
hpnicfevtModuleSw-LSX1SUP10A1                 OBJECT IDENTIFIER ::= { hpnicfevtModuleSwitchType 1239 } -- Supervisor Engine Board
hpnicfevtModuleSw-LSX1SUP16A1                 OBJECT IDENTIFIER ::= { hpnicfevtModuleSwitchType 1240 } -- Supervisor Engine Board
hpnicfevtModuleSw-LSX1FAB10B0                 OBJECT IDENTIFIER ::= { hpnicfevtModuleSwitchType 1241 } -- Switch Fabric Board
hpnicfevtModuleSw-LSX1FAB16B0                 OBJECT IDENTIFIER ::= { hpnicfevtModuleSwitchType 1242 } -- Switch Fabric Board
hpnicfevtModuleSw-LSX1FAB10B1                 OBJECT IDENTIFIER ::= { hpnicfevtModuleSwitchType 1243 } -- Switch Fabric Board
hpnicfevtModuleSw-LSX1FAB16B1                 OBJECT IDENTIFIER ::= { hpnicfevtModuleSwitchType 1244 } -- Switch Fabric Board
hpnicfevtModuleSw-LSX1QGS16EA0                OBJECT IDENTIFIER ::= { hpnicfevtModuleSwitchType 1245 } -- Switch Fabric Board16-Port 40G BASE Ethernet Optical Interface Board(QSFP+,MPO)
hpnicfevtModuleSw-LSX1TGS48EA0                OBJECT IDENTIFIER ::= { hpnicfevtModuleSwitchType 1246 } -- 48-Port 10GBASE Ethernet SFP+ Optical Interface Board
hpnicfevtModuleSw-LSX1QGS16EA1                OBJECT IDENTIFIER ::= { hpnicfevtModuleSwitchType 1247 } -- Switch Fabric Board16-Port 40G BASE Ethernet Optical Interface Board(QSFP+,MPO)
hpnicfevtModuleSw-LSX1TGS48EA1                OBJECT IDENTIFIER ::= { hpnicfevtModuleSwitchType 1248 } -- 48-Port 10GBASE Ethernet SFP+ Optical Interface Board
hpnicfevtModuleSw-LSU1TGT24SF9                OBJECT IDENTIFIER ::= { hpnicfevtModuleSwitchType 1249 } -- 24-Port 10GBASE-T Ethernet Electrical Interface Board(RJ45)(SF)
hpnicfevtModuleSw-LSU1QGS8SF9                 OBJECT IDENTIFIER ::= { hpnicfevtModuleSwitchType 1250 } -- 8-Port 40G BASE Ethernet Optical Interface Board(QSFP+,MPO)(SF)
hpnicfevtModuleSw-LSU1QGS4SF9                 OBJECT IDENTIFIER ::= { hpnicfevtModuleSwitchType 1251 } -- 4-Port 40GBASE Ethernet QSFP+ Optical Interface Board(QSFP+,MPO)(SF)
hpnicfevtModuleSw-LSU1TGS48SF9                OBJECT IDENTIFIER ::= { hpnicfevtModuleSwitchType 1252 } -- 48-Port 10GBASE Ethernet SFP+ Optical Interface Board
hpnicfevtModuleSw-LSU1TGS32SF9                OBJECT IDENTIFIER ::= { hpnicfevtModuleSwitchType 1253 } -- 32-Port 10GBASE Ethernet SFP+ Optical Interface Board
hpnicfevtModuleSw-LSU1FAB08D9                 OBJECT IDENTIFIER ::= { hpnicfevtModuleSwitchType 1254 } -- Switching Fabric Module
hpnicfevtModuleSw-LSU1SUPB9                   OBJECT IDENTIFIER ::= { hpnicfevtModuleSwitchType 1255 } -- Supervisor Engine Board
hpnicfevtModuleSw-LSQ3GV48SC0                 OBJECT IDENTIFIER ::= { hpnicfevtModuleSwitchType 1256 } -- 48-Port 1000Base-T Gigabit Ethernet Interface Board(RJ45), PoE Plus
hpnicfevtModuleSw-LSX1QGS12EC1                OBJECT IDENTIFIER ::= { hpnicfevtModuleSwitchType 1257 } -- 12-Port 40GBASE Ethernet Optical Interface Board(QSFP+)
hpnicfevtModuleSw-LSX1QGS12EC0                OBJECT IDENTIFIER ::= { hpnicfevtModuleSwitchType 1258 } -- 12-Port 40GBASE Ethernet Optical Interface Board(QSFP+)
hpnicfevtModuleSw-LSX1TGS48EC0                OBJECT IDENTIFIER ::= { hpnicfevtModuleSwitchType 1259 } -- 48-Port 10GBASE Ethernet SFP+ Optical Interface Board
hpnicfevtModuleSw-LSX1TGS48EC1                OBJECT IDENTIFIER ::= { hpnicfevtModuleSwitchType 1260 } -- 48-Port 10GBASE Ethernet SFP+ Optical Interface Board
hpnicfevtModuleSw-LSX1TGS24EC0                OBJECT IDENTIFIER ::= { hpnicfevtModuleSwitchType 1261 } -- 24-Port 10GBASE Ethernet SFP+ Optical Interface Board(EC)
hpnicfevtModuleSw-LSX1TGS24EC1                OBJECT IDENTIFIER ::= { hpnicfevtModuleSwitchType 1262 } -- 24-Port 10GBASE Ethernet SFP+ Optical Interface Board(EC)
hpnicfevtModuleSw-LSX1FAB10A0                 OBJECT IDENTIFIER ::= { hpnicfevtModuleSwitchType 1263 } -- Switch Fabric Board,For 10 Slots Chassis
hpnicfevtModuleSw-LSX1FAB16A1                 OBJECT IDENTIFIER ::= { hpnicfevtModuleSwitchType 1264 } -- Switch Fabric Board,For 16 Slots Chassis
hpnicfevtModuleSw-LSX1QGS12FB0                OBJECT IDENTIFIER ::= { hpnicfevtModuleSwitchType 1265 } -- 12-Port 40GBASE Ethernet Optical Interface Board(QSFP+)
hpnicfevtModuleSw-LSX1TGS24FB0                OBJECT IDENTIFIER ::= { hpnicfevtModuleSwitchType 1266 } -- 24-Port 10GBASE Ethernet SFP+ Optical Interface Board(FB)
hpnicfevtModuleSw-LSX1TGS48FB0                OBJECT IDENTIFIER ::= { hpnicfevtModuleSwitchType 1267 } -- 48-Port 10GBASE Ethernet SFP+ Optical Interface Board(FB)
hpnicfevtModuleSw-LSX1QGS12EB1                OBJECT IDENTIFIER ::= { hpnicfevtModuleSwitchType 1268 } -- 12-Port 40GBASE Ethernet Optical Interface Board(QSFP+)
hpnicfevtModuleSw-LSX1TGS24EB1                OBJECT IDENTIFIER ::= { hpnicfevtModuleSwitchType 1269 } -- 24-Port 10GBASE Ethernet SFP+ Optical Interface Board(EB)
hpnicfevtModuleSw-LSX1FAB10A1                 OBJECT IDENTIFIER ::= { hpnicfevtModuleSwitchType 1270 } -- Switch Fabric Board,For 10 Slots Chassis
hpnicfevtModuleSw-LSX1TGS48EB1                OBJECT IDENTIFIER ::= { hpnicfevtModuleSwitchType 1271 } -- 48-Port 10GBASE Ethernet SFP+ Optical Interface Board(EB)
hpnicfevtModuleSw-LSX1GP48EB1                 OBJECT IDENTIFIER ::= { hpnicfevtModuleSwitchType 1272 } -- 44-Port GE Optical Interface(SFP,LC)+4-Port 10GE Optical Interface Board(SFP+,LC)
hpnicfevtModuleSw-LSX1GP48FB0                 OBJECT IDENTIFIER ::= { hpnicfevtModuleSwitchType 1273 } -- 44-Port GE Optical Interface(SFP,LC)+4-Port 10GE Optical Interface Board(SFP+,LC)
hpnicfevtModuleSw-LSX1GT48FC0                 OBJECT IDENTIFIER ::= { hpnicfevtModuleSwitchType 1274 } -- 48-Port 1000Base-T Gigabit Ethernet Interface Module(RJ45)(FC)
hpnicfevtModuleSw-LSX1GT48FC1                 OBJECT IDENTIFIER ::= { hpnicfevtModuleSwitchType 1275 } -- 48-Port 1000Base-T Gigabit Ethernet Interface Module(RJ45)(FC)
hpnicfevtModuleSw-LSX1GP48FC0                 OBJECT IDENTIFIER ::= { hpnicfevtModuleSwitchType 1276 } -- 48-Port 1000BASE-X Gigabit Ethernet Optical Interface Module(SFP,LC)(FC)
hpnicfevtModuleSw-LSX1GP48FC1                 OBJECT IDENTIFIER ::= { hpnicfevtModuleSwitchType 1277 } -- 48-Port 1000BASE-X Gigabit Ethernet Optical Interface Module(SFP,LC)(FC)
hpnicfevtModuleSw-LSX1QGS12FC0                OBJECT IDENTIFIER ::= { hpnicfevtModuleSwitchType 1278 } -- 12-Port 40GBASE Ethernet Optical Interface Module(QSFP+)(FC)
hpnicfevtModuleSw-LSX1QGS12FC1                OBJECT IDENTIFIER ::= { hpnicfevtModuleSwitchType 1279 } -- 12-Port 40GBASE Ethernet Optical Interface Module(QSFP+)(FC)
hpnicfevtModuleSw-LSX2TGS48EA1                OBJECT IDENTIFIER ::= { hpnicfevtModuleSwitchType 1280 } -- 48-Port 10GBASE Ethernet SFP+ Optical Interface Board(EA)
hpnicfevtModuleSw-LSX1CGC4EB1                 OBJECT IDENTIFIER ::= { hpnicfevtModuleSwitchType 1281 } -- 4-Port 100GBASE Ethernet Optical Interface Board(CFP),Monolithic
hpnicfevtModuleSw-LSX1CGC4EC0                 OBJECT IDENTIFIER ::= { hpnicfevtModuleSwitchType 1282 } -- 4-Port 100GBASE Ethernet Optical Interface Board(CFP),Monolithic
hpnicfevtModuleSw-LSX1GT48EB1                 OBJECT IDENTIFIER ::= { hpnicfevtModuleSwitchType 1283 } -- 48-Port 1000Base-T Gigabit Ethernet Interface Board(RJ45)
hpnicfevtModuleSw-LSX1GT48FB0                 OBJECT IDENTIFIER ::= { hpnicfevtModuleSwitchType 1284 } -- 48-Port 1000Base-T Gigabit Ethernet Interface Board(RJ45)
hpnicfevtModuleSw-LSX1FAB16S1                 OBJECT IDENTIFIER ::= { hpnicfevtModuleSwitchType 1285 } -- Switch Fabric Board,For 16 Slots Chassis
hpnicfevtModuleSw-LSQ1SUPB3                   OBJECT IDENTIFIER ::= { hpnicfevtModuleSwitchType 1286 } -- Supervisor Engine Board
hpnicfevtModuleSw-LSU1CGC2SE0                 OBJECT IDENTIFIER ::= { hpnicfevtModuleSwitchType 1287 } -- 2 Port 100GBASE Ethernet Optical Interface Board(CFP)(SE)
hpnicfevtModuleSw-LSU1TGS16SF0                OBJECT IDENTIFIER ::= { hpnicfevtModuleSwitchType 1288 } -- 16-Port 10GBASE Ethernet SFP+ Optical Interface Board
hpnicfevtModuleSw-LSU1TGS8SF0                 OBJECT IDENTIFIER ::= { hpnicfevtModuleSwitchType 1289 } -- 8-Port 10GBASE Ethernet SFP+ Optical Interface Board
hpnicfevtModuleSw-LSQ1TGS4SC0                 OBJECT IDENTIFIER ::= { hpnicfevtModuleSwitchType 1290 } -- 4-Port 10GBASE Ethernet SFP+ Optical Interface Board
hpnicfevtModuleSw-LSU1GT48SE3                 OBJECT IDENTIFIER ::= { hpnicfevtModuleSwitchType 1291 } -- 48-Port 1000Base-T Gigabit Ethernet Interface Board(RJ45)
hpnicfevtModuleSw-LSU1GP48SE3                 OBJECT IDENTIFIER ::= { hpnicfevtModuleSwitchType 1292 } -- 48-Port 1000BASE Ethernet Optical Interface Board(SFP,LC)
hpnicfevtModuleSw-LSX1SUP10B0                 OBJECT IDENTIFIER ::= { hpnicfevtModuleSwitchType 1293 } -- Supervisor Engine Board
hpnicfevtModuleSw-LSX1SUP16B0                 OBJECT IDENTIFIER ::= { hpnicfevtModuleSwitchType 1294 } -- Supervisor Engine Board
hpnicfevtModuleSw-LSX1SUP10B1                 OBJECT IDENTIFIER ::= { hpnicfevtModuleSwitchType 1295 } -- Supervisor Engine Board
hpnicfevtModuleSw-LSX1SUP16B1                 OBJECT IDENTIFIER ::= { hpnicfevtModuleSwitchType 1296 } -- Supervisor Engine Board
hpnicfevtModuleSw-LSQ1CGV24PSC3               OBJECT IDENTIFIER ::= { hpnicfevtModuleSwitchType 1297 } -- Switching and Routing Processing Unit with 24 10/100/1000BASE-T Electrical Ports(RJ45),including 4 Combo Ports,SFP Req,PoE,No Spell
hpnicfevtModuleSw-LSQ1SRPA8                   OBJECT IDENTIFIER ::= { hpnicfevtModuleSwitchType 1298 } -- Supervisor Engine Board
hpnicfevtModuleSw-LSQ1CGP24TSC8               OBJECT IDENTIFIER ::= { hpnicfevtModuleSwitchType 1299 } -- Supervisor Engine Board
hpnicfevtModuleSw-LSQ1CGT24PSC8               OBJECT IDENTIFIER ::= { hpnicfevtModuleSwitchType 1300 } -- Supervisor Engine Board
hpnicfevtModuleSw-LSQ1GT24PSA8                OBJECT IDENTIFIER ::= { hpnicfevtModuleSwitchType 1301 } -- 24-Port 10/100/1000BASE-T Electrical(RJ45) Interface Board,including 4 Combo Ports,SFP Req,Upgradeable to PoE
hpnicfevtModuleSw-LSQ1GP24TSA8                OBJECT IDENTIFIER ::= { hpnicfevtModuleSwitchType 1302 } -- 16-Port 1000BASE-X Gigabit Ethernet Optical(SFP,LC) And 8-Port 10/100/1000BASE-T RJ45/1000BASE-X SFP Combo Interface Board
hpnicfevtModuleSw-LSQ1GT48SA8                 OBJECT IDENTIFIER ::= { hpnicfevtModuleSwitchType 1303 } -- 48-Port 1000Base-T Gigabit Ethernet Interface Board(RJ45)
hpnicfevtModuleSw-LSQ1GP48SA8                 OBJECT IDENTIFIER ::= { hpnicfevtModuleSwitchType 1304 } -- 48-Port 1000BASE-X Ethernet Optical Interface Board(SFP,LC)
hpnicfevtModuleSw-LSQ1TGS4SC8                 OBJECT IDENTIFIER ::= { hpnicfevtModuleSwitchType 1305 } -- 4-Port 10GBASE Ethernet SFP+ Optical Interface Board
hpnicfevtModuleSw-LSQ1TGS8SC8                 OBJECT IDENTIFIER ::= { hpnicfevtModuleSwitchType 1306 } -- 8-Port 10GBASE Ethernet SFP+ Optical Interface Board
hpnicfevtModuleSw-LSU1GT24SE3                 OBJECT IDENTIFIER ::= { hpnicfevtModuleSwitchType 1307 } -- 24-Port 1000BASE-T Ethernet Interface Board (RJ45)
hpnicfevtModuleSw-LSU1GP12SE3                 OBJECT IDENTIFIER ::= { hpnicfevtModuleSwitchType 1308 } -- 12-Port 1000BASE-X Ethernet Optical Interface Board(SFP,LC)
hpnicfevtModuleSw-LSU1GP24SE3                 OBJECT IDENTIFIER ::= { hpnicfevtModuleSwitchType 1309 } -- 24 Port 1000BASE-X Ethernet Optical Interface Board(SFP,LC)
hpnicfevtModuleSw-LSU1T24XGSE3                OBJECT IDENTIFIER ::= { hpnicfevtModuleSwitchType 1310 } -- 24-Port 1000BASE-T Gigabit Ethernet Interface(RJ45)+2-Port 10GBASE Ethernet Optical Interface Board(XFP,LC)
hpnicfevtModuleSw-LSU1P24XGSE3                OBJECT IDENTIFIER ::= { hpnicfevtModuleSwitchType 1311 } -- 24-Port 1000BASE-X Gigabit Ethernet Optical Interface(SFP,LC)+2-Port 10GBASE Ethernet Optical Interface Board(XFP,LC)
hpnicfevtModuleSw-LSU1GP24TSE3                OBJECT IDENTIFIER ::= { hpnicfevtModuleSwitchType 1312 } -- 16-Port 1000BASE-X Gigabit Ethernet Optical(SFP,LC) And 8-Port 10/100/1000BASE-T RJ45/1000BASE-X SFP Combo Interface Board
hpnicfevtModuleSw-LSU1GT40PSE3                OBJECT IDENTIFIER ::= { hpnicfevtModuleSwitchType 1313 } -- 40-Port 10/100/1000BASE-T Electrical(RJ45) And 8-Port 1000BASE-X Optical Ethernet Interface Board(SFP,LC),PoE
hpnicfevtModuleSw-LSV1TGS24SA1                OBJECT IDENTIFIER ::= { hpnicfevtModuleSwitchType 1314 } -- 24-Port 10G BASE Ethernet Optical Interface Board(SFP+)
hpnicfevtModuleSw-LSV1SRPA1                   OBJECT IDENTIFIER ::= { hpnicfevtModuleSwitchType 1315 } -- Switching Fabric Module
hpnicfevtModuleSw-LSV1SRPC1                   OBJECT IDENTIFIER ::= { hpnicfevtModuleSwitchType 1316 } -- Switching Fabric Module
hpnicfevtModuleSw-LSX1FAB16S0                 OBJECT IDENTIFIER ::= { hpnicfevtModuleSwitchType 1317 } -- Switch Fabric Board,For 16 Slots Chassis
hpnicfevtModuleSw-LSU1WCME0                   OBJECT IDENTIFIER ::= { hpnicfevtModuleSwitchType 1318 } -- Access Controller Service Board
hpnicfevtModuleSw-EWPX1WCME0                  OBJECT IDENTIFIER ::= { hpnicfevtModuleSwitchType 1319 } -- Access Controller Service Board
hpnicfevtModuleSw-LSU1TGS48SG0                OBJECT IDENTIFIER ::= { hpnicfevtModuleSwitchType 1320 } -- 48-Port 10GBASE-R Ethernet SFP+ Optical Interface Board(SG)
hpnicfevtModuleSw-LSU1QGS12SG0                OBJECT IDENTIFIER ::= { hpnicfevtModuleSwitchType 1321 } -- 12-Port 40GBASE-R Ethernet QSFP+ Optical Interface Board(SG)
hpnicfevtModuleSw-LSU1GP44TSEC0               OBJECT IDENTIFIER ::= { hpnicfevtModuleSwitchType 1322 } -- 44-Port 1000BASE-R Ethernet SFP Optical Interface Board(EC)+4-Port 10GBASE-R Ethernet SFP+ Optical Interface Board(EC)
hpnicfevtModuleSw-LSU1TGS24EC0                OBJECT IDENTIFIER ::= { hpnicfevtModuleSwitchType 1323 } -- 24-Port 10GBASE-R Ethernet SFP+ Optical Interface Board(EC)
hpnicfevtModuleSw-LSU1QGS6EC0                 OBJECT IDENTIFIER ::= { hpnicfevtModuleSwitchType 1324 } -- 6-Port 40GBASE-R Ethernet QSFP+ Optical Interface Board(EC)
hpnicfevtModuleSw-LSU1CGC2EC0                 OBJECT IDENTIFIER ::= { hpnicfevtModuleSwitchType 1325 } -- 2-Port 100GBASE-R Ethernet CFP Optical Interface Board(EC)
hpnicfevtModuleSw-LSU1CGC2SE9                 OBJECT IDENTIFIER ::= { hpnicfevtModuleSwitchType 1326 } -- 2 Port 100GBASE Ethernet Optical Interface Board(CFP)(SE)
hpnicfevtModuleSw-LSXM1QGS24EX1               OBJECT IDENTIFIER ::= { hpnicfevtModuleSwitchType 1327 } -- 24 Ports 40G BASE Ethernet Optical Interface Board(QSFP+,MPO),No Spell
hpnicfevtModuleSw-LSXM1QGS24FB0               OBJECT IDENTIFIER ::= { hpnicfevtModuleSwitchType 1328 } -- 24 Ports 40G BASE Ethernet Optical Interface Board(QSFP+,MPO),No Spell
hpnicfevtModuleSw-LSVM1QGS12FX1               OBJECT IDENTIFIER ::= { hpnicfevtModuleSwitchType 1329 } -- 12-Port 40G BASE Ethernet Optical Interface Module(QSFP+,MPO/LC)
hpnicfevtModuleSw-LSVM1TGS24FX1               OBJECT IDENTIFIER ::= { hpnicfevtModuleSwitchType 1330 } -- 24-Port 10G BASE Ethernet Optical Interface Module(SFP+,LC)
hpnicfevtModuleSw-LSVM1QGS6C2FX1              OBJECT IDENTIFIER ::= { hpnicfevtModuleSwitchType 1331 } -- 2-Port 100GBASE Ethernet Optical Interface(CXP,MPO)+6-Port 40GBASE Ethernet Optical Interface(QSFP+,MPO/LC)+4-Port 10G BASE Ethernet Optical Interface Module(SFP+,LC)
hpnicfevtModuleSw-LSQ2GP44TSSC0               OBJECT IDENTIFIER ::= { hpnicfevtModuleSwitchType 1332 } -- 44-Port GE Optical Interface(SFP,LC)+4-Port 10GE Optical Interface Board(SFP+,LC)(SC)
hpnicfevtModuleSw-LSQ2GP44TSSC3               OBJECT IDENTIFIER ::= { hpnicfevtModuleSwitchType 1333 } -- 44-Port GE Optical Interface(SFP,LC)+4-Port 10GE Optical Interface Board(SFP+,LC)(SC)
hpnicfevtModuleSw-LSQ2GP24TSSC0               OBJECT IDENTIFIER ::= { hpnicfevtModuleSwitchType 1334 } -- 24-Port GE Optical Interface(SFP,LC)+4-Port 10GE Optical Interface Board(SFP+,LC)(SC)
hpnicfevtModuleSw-LSQ2GP24TSSC3               OBJECT IDENTIFIER ::= { hpnicfevtModuleSwitchType 1335 } -- 24-Port GE Optical Interface(SFP,LC)+4-Port 10GE Optical Interface Board(SFP+,LC)(SC)
hpnicfevtModuleSw-LSQ2GT24PTSSC0              OBJECT IDENTIFIER ::= { hpnicfevtModuleSwitchType 1336 } -- 24-Port 1000Base-T Gigabit Ethernet Interface Board(RJ45)+20-Port GE Optical Interface(SFP,LC)+4-Port 10GE Optical Interface Board(SFP+,LC)(SC)
hpnicfevtModuleSw-LSQ2GT24PTSSC3              OBJECT IDENTIFIER ::= { hpnicfevtModuleSwitchType 1337 } -- 24-Port 1000Base-T Gigabit Ethernet Interface Board(RJ45)+20-Port GE Optical Interface(SFP,LC)+4-Port 10GE Optical Interface Board(SFP+,LC)(SC)
hpnicfevtModuleSw-LSQ2GT24TSSC0               OBJECT IDENTIFIER ::= { hpnicfevtModuleSwitchType 1338 } -- 24-Port 1000Base-T Gigabit Ethernet Interface Board(RJ45)+4-Port 10GE Optical Interface Board(SFP+,LC)(SC)
hpnicfevtModuleSw-LSQ2GT24TSSC3               OBJECT IDENTIFIER ::= { hpnicfevtModuleSwitchType 1339 } -- 24-Port 1000Base-T Gigabit Ethernet Interface Board(RJ45)+4-Port 10GE Optical Interface Board(SFP+,LC)(SC)
hpnicfevtModuleSw-LSQ2GT48SC0                 OBJECT IDENTIFIER ::= { hpnicfevtModuleSwitchType 1340 } -- 48-Port 1000Base-T Gigabit Ethernet Interface Board(RJ45)(SC)
hpnicfevtModuleSw-LSQ2GT48SC3                 OBJECT IDENTIFIER ::= { hpnicfevtModuleSwitchType 1341 } -- 48-Port 1000Base-T Gigabit Ethernet Interface Board(RJ45)(SC)
hpnicfevtModuleSw-LSQ2GV48SC0                 OBJECT IDENTIFIER ::= { hpnicfevtModuleSwitchType 1342 } -- 48-Port 1000Base-T Gigabit Ethernet Interface Board(RJ45)(SC)-POE
hpnicfevtModuleSw-LSQ2GV48SC3                 OBJECT IDENTIFIER ::= { hpnicfevtModuleSwitchType 1343 } -- 48-Port 1000Base-T Gigabit Ethernet Interface Board(RJ45)(SC)-POE
hpnicfevtModuleSw-LSQ2TGS16SF0                OBJECT IDENTIFIER ::= { hpnicfevtModuleSwitchType 1344 } -- 16-Port 10GE Optical Interface Board(SFP+,LC)(SF)
hpnicfevtModuleSw-LSQ2TGS16SF3                OBJECT IDENTIFIER ::= { hpnicfevtModuleSwitchType 1345 } -- 16-Port 10GE Optical Interface Board(SFP+,LC)(SF)
hpnicfevtModuleSw-LSQ2MPUD0                   OBJECT IDENTIFIER ::= { hpnicfevtModuleSwitchType 1346 } -- Supervisor Engine Board
hpnicfevtModuleSw-LSQ2MPUD3                   OBJECT IDENTIFIER ::= { hpnicfevtModuleSwitchType 1347 } -- Supervisor Engine Board
hpnicfevtModuleSw-LSQ2MPUA0                   OBJECT IDENTIFIER ::= { hpnicfevtModuleSwitchType 1348 } -- Supervisor Engine Board
hpnicfevtModuleSw-LSQ2MPUA3                   OBJECT IDENTIFIER ::= { hpnicfevtModuleSwitchType 1349 } -- Supervisor Engine Board
hpnicfevtModuleSw-LSU2GP44TSSE0               OBJECT IDENTIFIER ::= { hpnicfevtModuleSwitchType 1350 } -- 44-Port GE Optical Interface(SFP,LC)+4-Port 10GE Optical Interface Board(SFP+,LC)(SE)
hpnicfevtModuleSw-LSU2GP44TSSE3               OBJECT IDENTIFIER ::= { hpnicfevtModuleSwitchType 1351 } -- 44-Port GE Optical Interface(SFP,LC)+4-Port 10GE Optical Interface Board(SFP+,LC)(SE)
hpnicfevtModuleSw-LSU2GP24TSSE0               OBJECT IDENTIFIER ::= { hpnicfevtModuleSwitchType 1352 } -- 24-Port GE Optical Interface(SFP,LC)+4-Port 10GE Optical Interface Board(SFP+,LC)(SE)
hpnicfevtModuleSw-LSU2GP24TSSE3               OBJECT IDENTIFIER ::= { hpnicfevtModuleSwitchType 1353 } -- 24-Port GE Optical Interface(SFP,LC)+4-Port 10GE Optical Interface Board(SFP+,LC)(SE)
hpnicfevtModuleSw-LSU2GT24PTSSE0              OBJECT IDENTIFIER ::= { hpnicfevtModuleSwitchType 1354 } -- 24-Port 1000Base-T Gigabit Ethernet Interface Board(RJ45)+20-Port GE Optical Interface(SFP,LC)+4-Port 10GE Optical Interface Board(SFP+,LC)(SE)
hpnicfevtModuleSw-LSU2GT24PTSSE3              OBJECT IDENTIFIER ::= { hpnicfevtModuleSwitchType 1355 } -- 24-Port 1000Base-T Gigabit Ethernet Interface Board(RJ45)+20-Port GE Optical Interface(SFP,LC)+4-Port 10GE Optical Interface Board(SFP+,LC)(SE)
hpnicfevtModuleSw-LSU2GT24TSSE0               OBJECT IDENTIFIER ::= { hpnicfevtModuleSwitchType 1356 } -- 24-Port 1000Base-T Gigabit Ethernet Interface Board(RJ45)+4-Port 10GE Optical Interface Board(SFP+,LC)(SE)
hpnicfevtModuleSw-LSU2GT24TSSE3               OBJECT IDENTIFIER ::= { hpnicfevtModuleSwitchType 1357 } -- 24-Port 1000Base-T Gigabit Ethernet Interface Board(RJ45)+4-Port 10GE Optical Interface Board(SFP+,LC)(SE)
hpnicfevtModuleSw-LSU2GT48SE0                 OBJECT IDENTIFIER ::= { hpnicfevtModuleSwitchType 1358 } -- 48-Port 1000Base-T Gigabit Ethernet Interface Board(RJ45)(SE)
hpnicfevtModuleSw-LSU2GT48SE3                 OBJECT IDENTIFIER ::= { hpnicfevtModuleSwitchType 1359 } -- 48-Port 1000Base-T Gigabit Ethernet Interface Board(RJ45)(SE)
hpnicfevtModuleSw-LSU2GV48SE0                 OBJECT IDENTIFIER ::= { hpnicfevtModuleSwitchType 1360 } -- 48-Port 1000Base-T Gigabit Ethernet Interface Board(RJ45)(SE)-POE
hpnicfevtModuleSw-LSU2GV48SE3                 OBJECT IDENTIFIER ::= { hpnicfevtModuleSwitchType 1361 } -- 48-Port 1000Base-T Gigabit Ethernet Interface Board(RJ45)(SE)-POE
hpnicfevtModuleSw-LSU2TGS16SF0                OBJECT IDENTIFIER ::= { hpnicfevtModuleSwitchType 1362 } -- 16-Port 10GE Optical Interface Board(SFP+,LC)(SF)
hpnicfevtModuleSw-LSU2TGS16SF3                OBJECT IDENTIFIER ::= { hpnicfevtModuleSwitchType 1363 } -- 16-Port 10GE Optical Interface Board(SFP+,LC)(SF)
hpnicfevtModuleSw-LSU1MPU06B0                 OBJECT IDENTIFIER ::= { hpnicfevtModuleSwitchType 1364 } -- Supervisor Engine Board
hpnicfevtModuleSw-LSU1MPU06B3                 OBJECT IDENTIFIER ::= { hpnicfevtModuleSwitchType 1365 } -- Supervisor Engine Board
hpnicfevtModuleSw-LSU1MPU10C0                 OBJECT IDENTIFIER ::= { hpnicfevtModuleSwitchType 1366 } -- Supervisor Engine Board
hpnicfevtModuleSw-LSU1MPU10C3                 OBJECT IDENTIFIER ::= { hpnicfevtModuleSwitchType 1367 } -- Supervisor Engine Board
hpnicfevtModuleSw-LSU1FAB06C0                 OBJECT IDENTIFIER ::= { hpnicfevtModuleSwitchType 1368 } -- Switching Fabric Module
hpnicfevtModuleSw-LSU1FAB06C3                 OBJECT IDENTIFIER ::= { hpnicfevtModuleSwitchType 1369 } -- Switching Fabric Module
hpnicfevtModuleSw-LSU1FAB10C0                 OBJECT IDENTIFIER ::= { hpnicfevtModuleSwitchType 1370 } -- Switching Fabric Module
hpnicfevtModuleSw-LSU1FAB10C3                 OBJECT IDENTIFIER ::= { hpnicfevtModuleSwitchType 1371 } -- Switching Fabric Module
hpnicfevtModuleSw-LSXM1SUPA1                  OBJECT IDENTIFIER ::= { hpnicfevtModuleSwitchType 1372 } -- Supervisor Engine Module
hpnicfevtModuleSw-LSXM1SFF16B1                OBJECT IDENTIFIER ::= { hpnicfevtModuleSwitchType 1373 } -- Switch Fabric Board

--
-- 1400 to 1599 reserved for switche RPU logical modules
--
hpnicfevtModulesw-PEX-Common                  OBJECT IDENTIFIER ::= { hpnicfevtModuleSwitchType 1400 } -- The general logical module type for PEX


-- Here define submodule for routers
hpnicfevtSubModuleRouter       OBJECT IDENTIFIER ::= { hpnicfevtModule 5 }


-- Here define submodule for switches
hpnicfevtSubModuleSwitch       OBJECT IDENTIFIER ::= { hpnicfevtModule 6 }

--
-- hpnicfevtPort section:
--
hpnicfevtPort          OBJECT IDENTIFIER ::= { hpnicfEntityVendortypeObjects 10 }

hpnicfevtPortUnknownPorts      OBJECT IDENTIFIER ::= { hpnicfevtPort 1 }
hpnicfevtPortCommonPorts       OBJECT IDENTIFIER ::= { hpnicfevtPort 2 }
hpnicfevtPortRouterType        OBJECT IDENTIFIER ::= { hpnicfevtPort 3 }
hpnicfevtPortSwitchType        OBJECT IDENTIFIER ::= { hpnicfevtPort 4 }


-- Below are ports used to router
hpnicfevtPortRt-Async          OBJECT IDENTIFIER ::= { hpnicfevtPortRouterType 1 }    -- Async interface
hpnicfevtPortRt-Analogmodem    OBJECT IDENTIFIER ::= { hpnicfevtPortRouterType 2 }    -- Analog modem interface
hpnicfevtPortRt-Atm            OBJECT IDENTIFIER ::= { hpnicfevtPortRouterType 3 }
hpnicfevtPortRt-AtmAdsl        OBJECT IDENTIFIER ::= { hpnicfevtPortRouterType 4 }
hpnicfevtPortRt-AtmShdsl       OBJECT IDENTIFIER ::= { hpnicfevtPortRouterType 5 }
hpnicfevtPortRt-AtmE1          OBJECT IDENTIFIER ::= { hpnicfevtPortRouterType 6 }
hpnicfevtPortRt-AtmT1          OBJECT IDENTIFIER ::= { hpnicfevtPortRouterType 7 }
hpnicfevtPortRt-AtmE3          OBJECT IDENTIFIER ::= { hpnicfevtPortRouterType 8 }
hpnicfevtPortRt-AtmT3          OBJECT IDENTIFIER ::= { hpnicfevtPortRouterType 9 }
hpnicfevtPortRt-Atm622M        OBJECT IDENTIFIER ::= { hpnicfevtPortRouterType 10 }
hpnicfevtPortRt-AtmImaE1       OBJECT IDENTIFIER ::= { hpnicfevtPortRouterType 11 }
hpnicfevtPortRt-AtmImaT1       OBJECT IDENTIFIER ::= { hpnicfevtPortRouterType 12 }
hpnicfevtPortRt-Atm25M         OBJECT IDENTIFIER ::= { hpnicfevtPortRouterType 13 }
hpnicfevtPortRt-Bri            OBJECT IDENTIFIER ::= { hpnicfevtPortRouterType 14 }
hpnicfevtPortRt-Console        OBJECT IDENTIFIER ::= { hpnicfevtPortRouterType 15 }
hpnicfevtPortRt-E1             OBJECT IDENTIFIER ::= { hpnicfevtPortRouterType 16 }
hpnicfevtPortRt-E3             OBJECT IDENTIFIER ::= { hpnicfevtPortRouterType 17 }
hpnicfevtPortRt-T1             OBJECT IDENTIFIER ::= { hpnicfevtPortRouterType 18 }
hpnicfevtPortRt-T3             OBJECT IDENTIFIER ::= { hpnicfevtPortRouterType 19 }
hpnicfevtPortRt-Cpos           OBJECT IDENTIFIER ::= { hpnicfevtPortRouterType 20 }
hpnicfevtPortRt-Ethernet       OBJECT IDENTIFIER ::= { hpnicfevtPortRouterType 21 }
hpnicfevtPortRt-Serial         OBJECT IDENTIFIER ::= { hpnicfevtPortRouterType 22 }
hpnicfevtPortRt-E1f            OBJECT IDENTIFIER ::= { hpnicfevtPortRouterType 23 }
hpnicfevtPortRt-T1f            OBJECT IDENTIFIER ::= { hpnicfevtPortRouterType 24 }
hpnicfevtPortRt-Pos            OBJECT IDENTIFIER ::= { hpnicfevtPortRouterType 25 }
hpnicfevtPortRt-Ge             OBJECT IDENTIFIER ::= { hpnicfevtPortRouterType 26 }
hpnicfevtPortRt-Aux            OBJECT IDENTIFIER ::= { hpnicfevtPortRouterType 27 }
-- hpnicfevtPortRt-Null         OBJECT IDENTIFIER ::= { hpnicfevtPortRouterType 28 }   reserved
-- hpnicfevtPortRt-Max          OBJECT IDENTIFIER ::= { hpnicfevtPortRouterType 29 }   reserved
hpnicfevtPortRt-VG-Fxs         OBJECT IDENTIFIER ::= { hpnicfevtPortRouterType 30 }
hpnicfevtPortRt-VG-Fxo         OBJECT IDENTIFIER ::= { hpnicfevtPortRouterType 31 }
hpnicfevtPortRt-VG-E1vi        OBJECT IDENTIFIER ::= { hpnicfevtPortRouterType 32 }
hpnicfevtPortRt-VG-T1vi        OBJECT IDENTIFIER ::= { hpnicfevtPortRouterType 33 }
hpnicfevtPortRt-Usb            OBJECT IDENTIFIER ::= { hpnicfevtPortRouterType 34 }
hpnicfevtPortRt-Ndec           OBJECT IDENTIFIER ::= { hpnicfevtPortRouterType 35 }   -- NDEC port, Encrypt card version 1.0
hpnicfevtPortRt-Cavium         OBJECT IDENTIFIER ::= { hpnicfevtPortRouterType 36 }   -- NDEC port, Encrypt card version 2.0
hpnicfevtPortRt-Fcm            OBJECT IDENTIFIER ::= { hpnicfevtPortRouterType 37 }   -- POS/Fast connect module port
hpnicfevtPortRt-E1vi           OBJECT IDENTIFIER ::= { hpnicfevtPortRouterType 38 }   -- E1VI port
hpnicfevtPortRt-T1vi           OBJECT IDENTIFIER ::= { hpnicfevtPortRouterType 39 }   -- T1VI port
hpnicfevtPortRt-Vi             OBJECT IDENTIFIER ::= { hpnicfevtPortRouterType 40 }   -- Voice port
hpnicfevtPortRt-Adls2Plus      OBJECT IDENTIFIER ::= { hpnicfevtPortRouterType 41 }   -- ADSL2Plus port
hpnicfevtPortRt-RADIO-AG       OBJECT IDENTIFIER ::= { hpnicfevtPortRouterType 42 }   -- 802.11ag Radio port
hpnicfevtPortRt-1exp           OBJECT IDENTIFIER ::= { hpnicfevtPortRouterType 43 }   -- 10GBASE-R/W Ethernet port
hpnicfevtPortRt-G-SHDSL-BIS    OBJECT IDENTIFIER ::= { hpnicfevtPortRouterType 44 }   -- 4 wire G.SHDSL.BIS interface
hpnicfevtPortRt-ONU-1000BASE-BX-SFF-SC    OBJECT IDENTIFIER ::= { hpnicfevtPortRouterType 45 }   -- 1000 BASE-BX SFF SC ONU Interface
hpnicfevtPortRt-CELLULAR       OBJECT IDENTIFIER ::= { hpnicfevtPortRouterType 46 }   -- 3G Wireless WAN Interface
hpnicfevtPortRt-CELLULAR-ETHERNET         OBJECT IDENTIFIER ::= { hpnicfevtPortRouterType 47 }   -- 3G Wireless WAN Interface for Ethernet mode
hpnicfevtPortRt-VGe            OBJECT IDENTIFIER ::= { hpnicfevtPortRouterType 48 } -- virtual Ge port
hpnicfevtPortRt-VXGe           OBJECT IDENTIFIER ::= { hpnicfevtPortRouterType 49 } -- virtual XGe port
hpnicfevtPortRt-Xpos           OBJECT IDENTIFIER ::= { hpnicfevtPortRouterType 50 } -- 10G POS port
hpnicfevtPortRt-Fge            OBJECT IDENTIFIER ::= { hpnicfevtPortRouterType 51 } -- 40G Ethernet port


-- Below are ports used to switches
--hpnicfevtPortSw-Unknown              OBJECT IDENTIFIER ::= { hpnicfevtPortSwitchType 0 }
hpnicfevtPortSw-10or100M               OBJECT IDENTIFIER ::= { hpnicfevtPortSwitchType 1 }
hpnicfevtPortSw-1000BaseLxSm           OBJECT IDENTIFIER ::= { hpnicfevtPortSwitchType 2 }
hpnicfevtPortSw-1000BaseSxMm           OBJECT IDENTIFIER ::= { hpnicfevtPortSwitchType 3 }
hpnicfevtPortSw-1000BaseTx             OBJECT IDENTIFIER ::= { hpnicfevtPortSwitchType 4 }
hpnicfevtPortSw-100MSinglemodeFx       OBJECT IDENTIFIER ::= { hpnicfevtPortSwitchType 5 }
hpnicfevtPortSw-100MMultimodeFx        OBJECT IDENTIFIER ::= { hpnicfevtPortSwitchType 6 }
hpnicfevtPortSw-100M100BaseTx          OBJECT IDENTIFIER ::= { hpnicfevtPortSwitchType 7 }
hpnicfevtPortSw-100MHub                OBJECT IDENTIFIER ::= { hpnicfevtPortSwitchType 8 }
hpnicfevtPortSw-Vdsl                   OBJECT IDENTIFIER ::= { hpnicfevtPortSwitchType 9 }
hpnicfevtPortSw-Stack                  OBJECT IDENTIFIER ::= { hpnicfevtPortSwitchType 10 }
hpnicfevtPortSw-1000BaseZenithFx       OBJECT IDENTIFIER ::= { hpnicfevtPortSwitchType 11 }
hpnicfevtPortSw-1000BaseLongFx         OBJECT IDENTIFIER ::= { hpnicfevtPortSwitchType 12 }
hpnicfevtPortSw-Adsl                   OBJECT IDENTIFIER ::= { hpnicfevtPortSwitchType 13 }
hpnicfevtPortSw-10or100MDb             OBJECT IDENTIFIER ::= { hpnicfevtPortSwitchType 14 }
hpnicfevtPortSw-10GBaseLrSm            OBJECT IDENTIFIER ::= { hpnicfevtPortSwitchType 15 }
hpnicfevtPortSw-10GBaseLx4Mm           OBJECT IDENTIFIER ::= { hpnicfevtPortSwitchType 16 }
hpnicfevtPortSw-10GBaseLx4Sm           OBJECT IDENTIFIER ::= { hpnicfevtPortSwitchType 17 }
hpnicfevtPortSw-100MLongFx             OBJECT IDENTIFIER ::= { hpnicfevtPortSwitchType 18 }
hpnicfevtPortSw-1000BaseCx             OBJECT IDENTIFIER ::= { hpnicfevtPortSwitchType 19 }
hpnicfevtPortSw-1000BaseZenithFxLc     OBJECT IDENTIFIER ::= { hpnicfevtPortSwitchType 20 }
hpnicfevtPortSw-1000BaseLongFxLc       OBJECT IDENTIFIER ::= { hpnicfevtPortSwitchType 21 }
hpnicfevtPortSw-100MSmFxSc             OBJECT IDENTIFIER ::= { hpnicfevtPortSwitchType 22 }
hpnicfevtPortSw-100MMmFxSc             OBJECT IDENTIFIER ::= { hpnicfevtPortSwitchType 23 }
hpnicfevtPortSw-100MSmFxLc             OBJECT IDENTIFIER ::= { hpnicfevtPortSwitchType 24 }
hpnicfevtPortSw-100MMmFxLc             OBJECT IDENTIFIER ::= { hpnicfevtPortSwitchType 25 }
hpnicfevtPortSw-GbicNoConnector        OBJECT IDENTIFIER ::= { hpnicfevtPortSwitchType 26 }
hpnicfevtPortSw-Gbic1000BaseT          OBJECT IDENTIFIER ::= { hpnicfevtPortSwitchType 27 }
hpnicfevtPortSw-Gbic1000BaseLx         OBJECT IDENTIFIER ::= { hpnicfevtPortSwitchType 28 }
hpnicfevtPortSw-Gbic1000BaseSx         OBJECT IDENTIFIER ::= { hpnicfevtPortSwitchType 29 }
hpnicfevtPortSw-Gbic1000BaseZx         OBJECT IDENTIFIER ::= { hpnicfevtPortSwitchType 30 }
hpnicfevtPortSw-ComboNoConnector       OBJECT IDENTIFIER ::= { hpnicfevtPortSwitchType 31 }
hpnicfevtPortSw-Combo1000BaseLx        OBJECT IDENTIFIER ::= { hpnicfevtPortSwitchType 32 }
hpnicfevtPortSw-Combo1000BaseLxFiber   OBJECT IDENTIFIER ::= { hpnicfevtPortSwitchType 33 }
hpnicfevtPortSw-Combo1000BaseLxCopper  OBJECT IDENTIFIER ::= { hpnicfevtPortSwitchType 34 }
hpnicfevtPortSw-Combo1000BaseSx        OBJECT IDENTIFIER ::= { hpnicfevtPortSwitchType 35 }
hpnicfevtPortSw-Combo1000BaseSxFiber   OBJECT IDENTIFIER ::= { hpnicfevtPortSwitchType 36 }
hpnicfevtPortSw-Combo1000BaseSxCopper  OBJECT IDENTIFIER ::= { hpnicfevtPortSwitchType 37 }
hpnicfevtPortSw-Combo1000BaseZx        OBJECT IDENTIFIER ::= { hpnicfevtPortSwitchType 38 }
hpnicfevtPortSw-Combo1000BaseZxFiber   OBJECT IDENTIFIER ::= { hpnicfevtPortSwitchType 39 }
hpnicfevtPortSw-Combo1000BaseZxCopper  OBJECT IDENTIFIER ::= { hpnicfevtPortSwitchType 40 }
hpnicfevtPortSw-155PosSxMmf            OBJECT IDENTIFIER ::= { hpnicfevtPortSwitchType 41 }
hpnicfevtPortSw-155PosLxSmf            OBJECT IDENTIFIER ::= { hpnicfevtPortSwitchType 42 }

-- added by Garibaldi
hpnicfevtPortSw-1000BASE-T             OBJECT IDENTIFIER ::= { hpnicfevtPortSwitchType 43 }  -- 1000 Base-T Port
hpnicfevtPortSw-1000BASE-SX-SFP        OBJECT IDENTIFIER ::= { hpnicfevtPortSwitchType 44 }  -- 1000 Base-SX SFP Port
hpnicfevtPortSw-1000BASE-LX-SFP        OBJECT IDENTIFIER ::= { hpnicfevtPortSwitchType 45 }  -- 1000 Base-LX SFP Port
hpnicfevtPortSw-1000BASE-T-AN-SFP      OBJECT IDENTIFIER ::= { hpnicfevtPortSwitchType 46 }  -- 1000 Base-T AN SFP Port
hpnicfevtPortSw-10GBASE-LX4-XENPAK     OBJECT IDENTIFIER ::= { hpnicfevtPortSwitchType 47 }  -- 10G Base-LX4 XENPAK Port
hpnicfevtPortSw-10GBASE-LR-XENPAK      OBJECT IDENTIFIER ::= { hpnicfevtPortSwitchType 48 }  -- 10G Base-LR XENPAK Port
hpnicfevtPortSw-10GBASE-CX4            OBJECT IDENTIFIER ::= { hpnicfevtPortSwitchType 49 }  -- 10G Base-CX4 Port
hpnicfevtPortSw-1000BASE-ZX-SFP        OBJECT IDENTIFIER ::= { hpnicfevtPortSwitchType 50 }  -- 1000 Base-ZX SFP Port
hpnicfevtPortSw-1000BASE-MM-SFP        OBJECT IDENTIFIER ::= { hpnicfevtPortSwitchType 51 }  -- 1000 Base-MM SFP Port
hpnicfevtPortSw-100BASE-SX-SFP         OBJECT IDENTIFIER ::= { hpnicfevtPortSwitchType 52 }  -- 100 Base-SX SFP Port
hpnicfevtPortSw-100BASE-LX-SFP         OBJECT IDENTIFIER ::= { hpnicfevtPortSwitchType 53 }  -- 100 Base-LX SFP Port
hpnicfevtPortSw-100BASE-T-AN-SFP       OBJECT IDENTIFIER ::= { hpnicfevtPortSwitchType 54 }  -- 100 Base-T SFP Port
hpnicfevtPortSw-100BASE-ZX-SFP         OBJECT IDENTIFIER ::= { hpnicfevtPortSwitchType 55 }  -- 100 Base-ZX SFP Port
hpnicfevtPortSw-100BASE-MM-SFP         OBJECT IDENTIFIER ::= { hpnicfevtPortSwitchType 56 }  -- 100 Base-MM SFP Port
hpnicfevtPortSw-SFP-NO-CONNECTOR       OBJECT IDENTIFIER ::= { hpnicfevtPortSwitchType 57 }  -- No Connector SFP Port
hpnicfevtPortSw-SFP-UNKNOWN-CONNECTOR  OBJECT IDENTIFIER ::= { hpnicfevtPortSwitchType 58 }  -- Unknown SFP Port
hpnicfevtPortSw-POS-NO-CONNECTOR       OBJECT IDENTIFIER ::= { hpnicfevtPortSwitchType 59 }  -- POS no connector
hpnicfevtPortSw-10G-BASE-SR            OBJECT IDENTIFIER ::= { hpnicfevtPortSwitchType 60 }  -- 10GBASE-SR Fiber Optic Transceivers with SC Connector
hpnicfevtPortSw-10G-BASE-ER            OBJECT IDENTIFIER ::= { hpnicfevtPortSwitchType 61 }  -- 10GBASE-ER Fiber Optic Transceivers with SC Connector
hpnicfevtPortSw-10G-BASE-LX4           OBJECT IDENTIFIER ::= { hpnicfevtPortSwitchType 62 }  -- 10GBASE-LX4 Fiber Optic Transceivers with SC Connector
hpnicfevtPortSw-10G-BASE-SW            OBJECT IDENTIFIER ::= { hpnicfevtPortSwitchType 63 }  -- 10GBASE-SW Fiber Optic Transceivers with SC Connector
hpnicfevtPortSw-10G-BASE-LW            OBJECT IDENTIFIER ::= { hpnicfevtPortSwitchType 64 }  -- 10GBASE-LW Fiber Optic Transceivers with SC Connector
hpnicfevtPortSw-10G-BASE-EW            OBJECT IDENTIFIER ::= { hpnicfevtPortSwitchType 65 }  -- 10GBASE-EW Fiber Optic Transceivers with SC Connector
hpnicfevtPortSw-10G-LR-SM-LC           OBJECT IDENTIFIER ::= { hpnicfevtPortSwitchType 66 }  -- 10GBASE-LR Single Mode Fiber Optic Transceivers with LC Connector
hpnicfevtPortSw-10G-SR-MM-LC           OBJECT IDENTIFIER ::= { hpnicfevtPortSwitchType 67 }  -- 10GBASE-SR Multi Mode Fiber Optic Transceivers with LC Connector
hpnicfevtPortSw-10G-ER-SM-LC           OBJECT IDENTIFIER ::= { hpnicfevtPortSwitchType 68 }  -- 10GBASE-ER Single Mode Fiber Optic Transceivers with LC Connector
hpnicfevtPortSw-10G-LW-SM-LC           OBJECT IDENTIFIER ::= { hpnicfevtPortSwitchType 69 }  -- 10GBASE-LW Single Mode Fiber Optic Transceivers with LC Connector
hpnicfevtPortSw-10G-SW-MM-LC           OBJECT IDENTIFIER ::= { hpnicfevtPortSwitchType 70 }  -- 10GBASE-SW Multi Mode Fiber Optic Transceivers with LC Connector
hpnicfevtPortSw-10G-EW-SM-LC           OBJECT IDENTIFIER ::= { hpnicfevtPortSwitchType 71 }  -- 10GBASE-EW Single Mode Fiber Optic Transceivers with LC Connector
hpnicfevtPortSw-100BASE-SM-MTRJ        OBJECT IDENTIFIER ::= { hpnicfevtPortSwitchType 72 }  -- 100 Base-SM MTRJ Port
hpnicfevtPortSw-100BASE-MM-MTRJ        OBJECT IDENTIFIER ::= { hpnicfevtPortSwitchType 73 }  -- 100 Base-MM MTRJ Port
hpnicfevtPortSw-XFP-NO-CONNECTOR       OBJECT IDENTIFIER ::= { hpnicfevtPortSwitchType 74 }  -- XFP without Transceiver
hpnicfevtPortSw-XFP-10GBASE-SR         OBJECT IDENTIFIER ::= { hpnicfevtPortSwitchType 75 }  -- 10GBASE-SR XFP Transceiver
hpnicfevtPortSw-XFP-10GBASE-LR         OBJECT IDENTIFIER ::= { hpnicfevtPortSwitchType 76 }  -- 10GBASE-LR XFP Transceiver
hpnicfevtPortSw-XFP-10GBASE-ER         OBJECT IDENTIFIER ::= { hpnicfevtPortSwitchType 77 }  -- 10GBASE-ER XFP Transceiver
hpnicfevtPortSw-XFP-10GBASE-SW         OBJECT IDENTIFIER ::= { hpnicfevtPortSwitchType 78 }  -- 10GBASE-SW XFP Transceiver
hpnicfevtPortSw-XFP-10GBASE-LW         OBJECT IDENTIFIER ::= { hpnicfevtPortSwitchType 79 }  -- 10GBASE-LW XFP Transceiver
hpnicfevtPortSw-XFP-10GBASE-EW         OBJECT IDENTIFIER ::= { hpnicfevtPortSwitchType 80 }  -- 10GBASE-EW XFP Transceiver
hpnicfevtPortSw-XFP-10GBASE-CX4        OBJECT IDENTIFIER ::= { hpnicfevtPortSwitchType 81 }  -- 10GBASE-CX4 XFP Transceiver
hpnicfevtPortSw-XFP-10GBASE-LX4        OBJECT IDENTIFIER ::= { hpnicfevtPortSwitchType 82 }  -- 10GBASE-LX4 XFP Transceiver
hpnicfevtPortSw-XFP-UNKNOWN            OBJECT IDENTIFIER ::= { hpnicfevtPortSwitchType 83 }  -- Unknown  XFP Transceiver
hpnicfevtPortSw-XPK-NOCONNECTOR        OBJECT IDENTIFIER ::= { hpnicfevtPortSwitchType 84 }  -- Xenpak without Transceiver
hpnicfevtPortSw-XPK-10GBASE-SR         OBJECT IDENTIFIER ::= { hpnicfevtPortSwitchType 85 }  -- 10GBASE-SR Xenpak Transceiver
hpnicfevtPortSw-XPK-10GBASE-LR         OBJECT IDENTIFIER ::= { hpnicfevtPortSwitchType 86 }  -- 10GBASE-LR Xenpak Transceiver
hpnicfevtPortSw-XPK-10GBASE-ER         OBJECT IDENTIFIER ::= { hpnicfevtPortSwitchType 87 }  -- 10GBASE-ER Xenpak Transceiver
hpnicfevtPortSw-XPK-10GBASE-SW         OBJECT IDENTIFIER ::= { hpnicfevtPortSwitchType 88 }  -- 10GBASE-SW Xenpak Transceiver
hpnicfevtPortSw-XPK-10GBASE-LW         OBJECT IDENTIFIER ::= { hpnicfevtPortSwitchType 89 }  -- 10GBASE-LW Xenpak Transceiver
hpnicfevtPortSw-XPK-10GBASE-EW         OBJECT IDENTIFIER ::= { hpnicfevtPortSwitchType 90 }  -- 10GBASE-EW Xenpak Transceiver
hpnicfevtPortSw-XPK-10GBASE-CX4        OBJECT IDENTIFIER ::= { hpnicfevtPortSwitchType 91 }  -- 10GBASE-CX4 Xenpak Transceiver
hpnicfevtPortSw-XPK-10GBASE-LX4        OBJECT IDENTIFIER ::= { hpnicfevtPortSwitchType 92 }  -- 10GBASE-LX4 Xenpak Transceiver
hpnicfevtPortSw-XPK-UNKNOWN            OBJECT IDENTIFIER ::= { hpnicfevtPortSwitchType 93 }  -- Unknown Xenpak Transceiver
hpnicfevtPortSw-POS-OC48-SR-SM-LC      OBJECT IDENTIFIER ::= { hpnicfevtPortSwitchType 94 }  -- OC48-SR Single Mode Fiber Optic Transceivers with LC Connector
hpnicfevtPortSw-POS-OC48-IR-SM-LC      OBJECT IDENTIFIER ::= { hpnicfevtPortSwitchType 95 }  -- OC48-IR Single Mode Fiber Optic Transceivers with LC Connector
hpnicfevtPortSw-POS-OC48-LR-SM-LC      OBJECT IDENTIFIER ::= { hpnicfevtPortSwitchType 96 }  -- OC48-LR Single Mode Fiber Optic Transceivers with LC Connector
hpnicfevtPortSw-10G-BASE-CX4           OBJECT IDENTIFIER ::= { hpnicfevtPortSwitchType 97 }  -- 10G BASE-CX4 Electrical Interface
hpnicfevtPortSw-OLT-1000BASE-BX-SFF-SC OBJECT IDENTIFIER ::= { hpnicfevtPortSwitchType 98 }  -- 1000 BASE-BX SFF SC OLT Interface
hpnicfevtPortSw-ONU-1000BASE-BX-SFF-SC OBJECT IDENTIFIER ::= { hpnicfevtPortSwitchType 99 }  -- 1000 BASE-BX SFF SC ONU Interface
hpnicfevtPortSw-24G-CASCADE            OBJECT IDENTIFIER ::= { hpnicfevtPortSwitchType 100 }  -- 24G Cascade port
hpnicfevtPortSw-POS-OC3-SR-MM          OBJECT IDENTIFIER ::= { hpnicfevtPortSwitchType 101 }  -- STM1/OC3 Short Reach Multi Mode Fiber Optic Transceivers with LC Connector
hpnicfevtPortSw-POS-OC3-IR-SM          OBJECT IDENTIFIER ::= { hpnicfevtPortSwitchType 102 }  -- STM1/OC3 Intermediate Reach Single Mode Fiber Optic Transceivers with LC Connector
hpnicfevtPortSw-POS-OC3-IR-1-SM        OBJECT IDENTIFIER ::= { hpnicfevtPortSwitchType 103 }  -- STM1/OC3 Intermediate Reach Single Mode Fiber Optic Transceivers with LC Connector(variation 1)
hpnicfevtPortSw-POS-OC3-IR-2-SM        OBJECT IDENTIFIER ::= { hpnicfevtPortSwitchType 104 }  -- STM1/OC3 Intermediate Reach Single Mode Fiber Optic Transceivers with LC Connector(variation 2)
hpnicfevtPortSw-POS-OC3-LR-SM          OBJECT IDENTIFIER ::= { hpnicfevtPortSwitchType 105 }  -- STM1/OC3 Long Reach Single Mode Fiber Optic Transceivers with LC Connector
hpnicfevtPortSw-POS-OC3-LR-1-SM        OBJECT IDENTIFIER ::= { hpnicfevtPortSwitchType 106 }  -- STM1/OC3 Long Reach Single Mode Fiber Optic Transceivers with LC Connector(variation 1)
hpnicfevtPortSw-POS-OC3-LR-2-SM        OBJECT IDENTIFIER ::= { hpnicfevtPortSwitchType 107 }  -- STM1/OC3 Long Reach Single Mode Fiber Optic Transceivers with LC Connector(variation 2)
hpnicfevtPortSw-POS-OC3-LR-3-SM        OBJECT IDENTIFIER ::= { hpnicfevtPortSwitchType 108 }  -- STM1/OC3 Long Reach Single Mode Fiber Optic Transceivers with LC Connector(variation 3)
hpnicfevtPortSw-POS-OC12-SR-MM         OBJECT IDENTIFIER ::= { hpnicfevtPortSwitchType 109 }  -- STM4/OC12 Short Reach Multi Mode Fiber Optic Transceivers with LC Connector
hpnicfevtPortSw-POS-OC12-IR-SM         OBJECT IDENTIFIER ::= { hpnicfevtPortSwitchType 110 }  -- STM4/OC12 Intermediate Reach Single Mode Fiber Optic Transceivers with LC Connector
hpnicfevtPortSw-POS-OC12-IR-1-SM       OBJECT IDENTIFIER ::= { hpnicfevtPortSwitchType 111 }  -- STM4/OC12 Intermediate Reach Single Mode Fiber Optic Transceivers with LC Connector(variation 1)
hpnicfevtPortSw-POS-OC12-IR-2-SM       OBJECT IDENTIFIER ::= { hpnicfevtPortSwitchType 112 }  -- STM4/OC12 Intermediate Reach Single Mode Fiber Optic Transceivers with LC Connector(variation 2)
hpnicfevtPortSw-POS-OC12-LR-SM         OBJECT IDENTIFIER ::= { hpnicfevtPortSwitchType 113 }  -- STM4/OC12 Long Reach Single Mode Fiber Optic Transceivers with LC Connector
hpnicfevtPortSw-POS-OC12-LR-1-SM       OBJECT IDENTIFIER ::= { hpnicfevtPortSwitchType 114 }  -- STM4/OC12 Long Reach Single Mode Fiber Optic Transceivers with LC Connector(variation 1)
hpnicfevtPortSw-POS-OC12-LR-2-SM       OBJECT IDENTIFIER ::= { hpnicfevtPortSwitchType 115 }  -- STM4/OC12 Long Reach Single Mode Fiber Optic Transceivers with LC Connector(variation 2)
hpnicfevtPortSw-POS-OC12-LR-3-SM       OBJECT IDENTIFIER ::= { hpnicfevtPortSwitchType 116 }  -- STM4/OC12 Long Reach Single Mode Fiber Optic Transceivers with LC Connector(variation 3)
hpnicfevtPortSw-POS-OC48-SR-SM         OBJECT IDENTIFIER ::= { hpnicfevtPortSwitchType 117 }  -- STM16/OC48 Short Reach Single Mode Fiber Optic Transceivers with LC Connector
hpnicfevtPortSw-POS-OC48-IR-SM         OBJECT IDENTIFIER ::= { hpnicfevtPortSwitchType 118 }  -- STM16/OC48 Intermediate Reach Single Mode Fiber Optic Transceivers with LC Connector
hpnicfevtPortSw-POS-OC48-IR-1-SM       OBJECT IDENTIFIER ::= { hpnicfevtPortSwitchType 119 }  -- STM16/OC48 Intermediate Reach Single Mode Fiber Optic Transceivers with LC Connector(variation 1)
hpnicfevtPortSw-POS-OC48-IR-2-SM       OBJECT IDENTIFIER ::= { hpnicfevtPortSwitchType 120 }  -- STM16/OC48 Intermediate Reach Single Mode Fiber Optic Transceivers with LC Connector(variation 2)
hpnicfevtPortSw-POS-OC48-LR-SM         OBJECT IDENTIFIER ::= { hpnicfevtPortSwitchType 121 }  -- STM16/OC48 Long Reach Single Mode Fiber Optic Transceivers with LC Connector
hpnicfevtPortSw-POS-OC48-LR-1-SM       OBJECT IDENTIFIER ::= { hpnicfevtPortSwitchType 122 }  -- STM16/OC48 Long Reach Single Mode Fiber Optic Transceivers with LC Connector(variation 1)
hpnicfevtPortSw-POS-OC48-LR-2-SM       OBJECT IDENTIFIER ::= { hpnicfevtPortSwitchType 123 }  -- STM16/OC48 Long Reach Single Mode Fiber Optic Transceivers with LC Connector(variation 2)
hpnicfevtPortSw-POS-OC48-LR-3-SM       OBJECT IDENTIFIER ::= { hpnicfevtPortSwitchType 124 }  -- STM16/OC48 Long Reach Single Mode Fiber Optic Transceivers with LC Connector(variation 3)
hpnicfevtPortSw-POS-I-64-1             OBJECT IDENTIFIER ::= { hpnicfevtPortSwitchType 125 }  -- STM64/OC192 Interconnect Fiber Optic Transceivers with LC Connector(wavelength 1310nm G.652 fiber)
hpnicfevtPortSw-POS-I-64-2             OBJECT IDENTIFIER ::= { hpnicfevtPortSwitchType 126 }  -- STM64/OC192 Interconnect Fiber Optic Transceivers with LC Connector(wavelength 1550nm G.652 fiber)
hpnicfevtPortSw-POS-I-64-3             OBJECT IDENTIFIER ::= { hpnicfevtPortSwitchType 127 }  -- STM64/OC192 Interconnect Fiber Optic Transceivers with LC Connector(wavelength 1550nm G.653 fiber)
hpnicfevtPortSw-POS-I-64-5             OBJECT IDENTIFIER ::= { hpnicfevtPortSwitchType 128 }  -- STM64/OC192 Interconnect Fiber Optic Transceivers with LC Connector(wavelength 1550nm G.655 fiber)
hpnicfevtPortSw-POS-S-64-1             OBJECT IDENTIFIER ::= { hpnicfevtPortSwitchType 129 }  -- STM64/OC192 Short Haul Fiber Optic Transceivers with LC Connector(wavelength 1310nm G.652 fiber)
hpnicfevtPortSw-POS-S-64-2             OBJECT IDENTIFIER ::= { hpnicfevtPortSwitchType 130 }  -- STM64/OC192 Short Haul Fiber Optic Transceivers with LC Connector(wavelength 1550nm G.652 fiber)
hpnicfevtPortSw-POS-S-64-3             OBJECT IDENTIFIER ::= { hpnicfevtPortSwitchType 131 }  -- STM64/OC192 Short Haul Fiber Optic Transceivers with LC Connector(wavelength 1550nm G.653 fiber)
hpnicfevtPortSw-POS-S-64-5             OBJECT IDENTIFIER ::= { hpnicfevtPortSwitchType 132 }  -- STM64/OC192 Short Haul Fiber Optic Transceivers with LC Connector(wavelength 1550nm G.655 fiber)
hpnicfevtPortSw-POS-L-64-1             OBJECT IDENTIFIER ::= { hpnicfevtPortSwitchType 133 }  -- STM64/OC192 Long Haul Fiber Optic Transceivers with LC Connector(wavelength 1310nm G.652 fiber)
hpnicfevtPortSw-POS-L-64-2             OBJECT IDENTIFIER ::= { hpnicfevtPortSwitchType 134 }  -- STM64/OC192 Long Haul Fiber Optic Transceivers with LC Connector(wavelength 1550nm G.652 fiber)
hpnicfevtPortSw-POS-L-64-3             OBJECT IDENTIFIER ::= { hpnicfevtPortSwitchType 135 }  -- STM64/OC192 Long Haul Fiber Optic Transceivers with LC Connector(wavelength 1550nm G.653 fiber)
hpnicfevtPortSw-POS-V-64-2             OBJECT IDENTIFIER ::= { hpnicfevtPortSwitchType 136 }  -- STM64/OC192 Very Long Haul Fiber Optic Transceivers with LC Connector(wavelength 1550nm G.652 fiber)
hpnicfevtPortSw-POS-V-64-3             OBJECT IDENTIFIER ::= { hpnicfevtPortSwitchType 137 }  -- STM64/OC192 Very Long Haul Fiber Optic Transceivers with LC Connector(wavelength 1550nm G.653 fiber)
hpnicfevtPortSw-100BASE-FX-BIDI        OBJECT IDENTIFIER ::= { hpnicfevtPortSwitchType 138 }  -- 100 BASE-FX BIDI Port
hpnicfevtPortSw-100BASE-BX10-U-SFP     OBJECT IDENTIFIER ::= { hpnicfevtPortSwitchType 139 }  -- 100 BASE-BX10-U-SFP Port
hpnicfevtPortSw-100BASE-BX10-D-SFP     OBJECT IDENTIFIER ::= { hpnicfevtPortSwitchType 140 }  -- 100 BASE-BX10-D-SFP Port
hpnicfevtPortSw-1000BASE-BX10-U-SFP    OBJECT IDENTIFIER ::= { hpnicfevtPortSwitchType 141 }  -- 1000 BASE-BX10-U-SFP Port
hpnicfevtPortSw-1000BASE-BX10-D-SFP    OBJECT IDENTIFIER ::= { hpnicfevtPortSwitchType 142 }  -- 1000 BASE-BX10-D-SFP Port
hpnicfevtPortSw-STK-1000BASE-T         OBJECT IDENTIFIER ::= { hpnicfevtPortSwitchType 143 }  -- 1000 BASE-T Stack Port
hpnicfevtPortSw-RPR-PHYPOS-CONNECTOR     OBJECT IDENTIFIER ::= { hpnicfevtPortSwitchType 144 }  -- Resilient Packet Ring POS physical port
hpnicfevtPortSw-RPR-PHY10GE-CONNECTOR    OBJECT IDENTIFIER ::= { hpnicfevtPortSwitchType 145 }  -- 10G Resilient Packet Ring physical port
hpnicfevtPortSw-RPR-LOGICPOS-CONNECTOR   OBJECT IDENTIFIER ::= { hpnicfevtPortSwitchType 146 }  -- Resilient Packet Ring POS logical port
hpnicfevtPortSw-RPR-LOGIC10GE-CONNECTOR  OBJECT IDENTIFIER ::= { hpnicfevtPortSwitchType 147 }  -- 10G Resilient Packet Ring logical port
hpnicfevtPortSw-10GBASE-ZR               OBJECT IDENTIFIER ::= { hpnicfevtPortSwitchType 148 }  -- Fiber Optic Transceivers with SC Connector, XENPAK
hpnicfevtPortSw-TYPE-ERROR-CONNECTOR     OBJECT IDENTIFIER ::= { hpnicfevtPortSwitchType 149 }  -- Error Optic Transceivers type
hpnicfevtPortSw-10G-STACK                OBJECT IDENTIFIER ::= { hpnicfevtPortSwitchType 150 }  -- 10G Stack Port
hpnicfevtPortSw-155-ATM-SX-MMF             OBJECT IDENTIFIER ::= { hpnicfevtPortSwitchType 151 }  -- ATM OC-3 Multi-mode Short Reach Optical Transceiver
hpnicfevtPortSw-155-ATM-LX-SMF             OBJECT IDENTIFIER ::= { hpnicfevtPortSwitchType 152 }  -- ATM OC-3 Single Mode Long Reach Optical Transceiver
hpnicfevtPortSw-622-ATM-SX-MMF             OBJECT IDENTIFIER ::= { hpnicfevtPortSwitchType 153 }  -- ATM OC-12 Multi-mode Short Reach Optical Transceiver
hpnicfevtPortSw-622-ATM-LX-SMF             OBJECT IDENTIFIER ::= { hpnicfevtPortSwitchType 154 }  -- ATM OC-12 Single Mode Long Reach Optical Transceiver
hpnicfevtPortSw-155-ATM-NO-CONNECTOR       OBJECT IDENTIFIER ::= { hpnicfevtPortSwitchType 155 }  -- ATM OC-3 No Connector
hpnicfevtPortSw-622-ATM-NO-CONNECTOR       OBJECT IDENTIFIER ::= { hpnicfevtPortSwitchType 156 }  -- ATM OC-12 No Connector
hpnicfevtPortSw-155-CPOS-E1-NO-CONNECTOR   OBJECT IDENTIFIER ::= { hpnicfevtPortSwitchType 157 }  -- CPOS(E1) OC-3 No Connector
hpnicfevtPortSw-155-CPOS-T1-NO-CONNECTOR   OBJECT IDENTIFIER ::= { hpnicfevtPortSwitchType 158 }  -- CPOS(T1) OC-3 No Connector
hpnicfevtPortSw-622-CPOS-E1-NO-CONNECTOR   OBJECT IDENTIFIER ::= { hpnicfevtPortSwitchType 159 }  -- CPOS(E1) OC-12 No Connector
hpnicfevtPortSw-622-CPOS-T1-NO-CONNECTOR   OBJECT IDENTIFIER ::= { hpnicfevtPortSwitchType 160 }  -- CPOS(T1) OC-12 No Connector
hpnicfevtPortSw-155-CPOS-E1-SX-MMF         OBJECT IDENTIFIER ::= { hpnicfevtPortSwitchType 161 }  -- CPOS(E1) OC-3 Multi-mode Short Reach Optical Transceiver
hpnicfevtPortSw-155-CPOS-T1-SX-MMF         OBJECT IDENTIFIER ::= { hpnicfevtPortSwitchType 162 }  -- CPOS(T1) OC-3 Multi-mode Short Reach Optical Transceiver
hpnicfevtPortSw-155-CPOS-E1-LX-SMF         OBJECT IDENTIFIER ::= { hpnicfevtPortSwitchType 163 }  -- CPOS(E1) OC-3 Single Mode Long Reach Optical Transceiver
hpnicfevtPortSw-155-CPOS-T1-LX-SMF         OBJECT IDENTIFIER ::= { hpnicfevtPortSwitchType 164 }  -- CPOS(T1) OC-3 Single Mode Long Reach Optical Transceiver
hpnicfevtPortSw-622-CPOS-E1-SX-MMF         OBJECT IDENTIFIER ::= { hpnicfevtPortSwitchType 165 }  -- CPOS(E1) OC-12 Multi-mode Short Reach Optical Transceiver
hpnicfevtPortSw-622-CPOS-T1-SX-MMF         OBJECT IDENTIFIER ::= { hpnicfevtPortSwitchType 166 }  -- CPOS(T1) OC-12 Multi-mode Short Reach Optical Transceiver
hpnicfevtPortSw-622-CPOS-E1-LX-SMF         OBJECT IDENTIFIER ::= { hpnicfevtPortSwitchType 167 }  -- CPOS(E1) OC-12 Multi-mode Short Reach Optical Transceiver
hpnicfevtPortSw-622-CPOS-T1-LX-SMF         OBJECT IDENTIFIER ::= { hpnicfevtPortSwitchType 168 }  -- CPOS(T1) OC-12 Single Mode Long Reach Optical Transceiver
hpnicfevtPortSw-E1-CONNECTOR               OBJECT IDENTIFIER ::= { hpnicfevtPortSwitchType 169 }  -- E1 RJ45 Transceiver
hpnicfevtPortSw-T1-CONNECTOR               OBJECT IDENTIFIER ::= { hpnicfevtPortSwitchType 170 }  -- T1 RJ45 Transceiver
hpnicfevtPortSw-1000BASE-STK-SFP           OBJECT IDENTIFIER ::= { hpnicfevtPortSwitchType 171 }  -- 1-port 1000 Base-STK SFP Module
hpnicfevtPortSw-1000BASE-BIDI-SFP          OBJECT IDENTIFIER ::= { hpnicfevtPortSwitchType 172 }  -- 1-port 1000 Base-BIDI SFP Module
hpnicfevtPortSw-1000BASE-CWDM-SFP          OBJECT IDENTIFIER ::= { hpnicfevtPortSwitchType 173 }  -- 1-port 1000 Base-CWDM SFP Module
hpnicfevtPortSw-100BASE-BIDI-SFP           OBJECT IDENTIFIER ::= { hpnicfevtPortSwitchType 174 }  -- 1-port 100 Base-BIDI SFP Module
hpnicfevtPortSw-OLT-1000BASE-PX-SFP        OBJECT IDENTIFIER ::= { hpnicfevtPortSwitchType 175 }  -- 1000BASE-PX SFP OLT Interface
hpnicfevtPortSw-OLT-1000BASE-NO-CONNECTOR  OBJECT IDENTIFIER ::= { hpnicfevtPortSwitchType 176 }  -- 1000BASE OLT No Connector
hpnicfevtPortSw-RPR-PHYGE-CONNECTOR        OBJECT IDENTIFIER ::= { hpnicfevtPortSwitchType 177 }  -- Resilient Packet Ring GE physical port
hpnicfevtPortSw-RPR-LOGICGE-CONNECTOR      OBJECT IDENTIFIER ::= { hpnicfevtPortSwitchType 178 }  -- Resilient Packet Ring GE logical port
hpnicfevtPortSw-100M-1550-BIDI             OBJECT IDENTIFIER ::= { hpnicfevtPortSwitchType 179 }  -- Single Port 100M Ethernet Bi-direction Optical Interface Module(TX1550nm, RX1310nm, 15km, SC)
hpnicfevtPortSw-100M-1310-BIDI             OBJECT IDENTIFIER ::= { hpnicfevtPortSwitchType 180 }  -- Single Port 100M Ethernet Bi-direction Optical reverse Interface Module(TX1310nm, RX1550nm, 15km, SC)
hpnicfevtPortSw-RPR-PHYOC48-CONNECTOR      OBJECT IDENTIFIER ::= { hpnicfevtPortSwitchType 181 }  -- Resilient Packet Ring OC48 physical port
hpnicfevtPortSw-RPR-LOGICOC48-CONNECTOR    OBJECT IDENTIFIER ::= { hpnicfevtPortSwitchType 182 }  -- Resilient Packet Ring OC48 logical port
hpnicfevtPortSw-100-1000-BASE-LX-SMF       OBJECT IDENTIFIER ::= { hpnicfevtPortSwitchType 183 }  -- 100BASE-LX/1000BASE-LX Single Mode Fiber Optic Transceivers
hpnicfevtPortSw-10G-ZW-SM-LC               OBJECT IDENTIFIER ::= { hpnicfevtPortSwitchType 184 }  -- 10GBASE-ZW Single Mode Fiber Optic Transceivers with LC Connector
hpnicfevtPortSw-10G-ZR-SM-LC               OBJECT IDENTIFIER ::= { hpnicfevtPortSwitchType 185 }  -- 10GBASE-ZR Single Mode Fiber Optic Transceivers with LC Connector
hpnicfevtPortSw-XPK-10GBASE-ZR             OBJECT IDENTIFIER ::= { hpnicfevtPortSwitchType 186 }  -- 10GBASE-ZR Xenpak Transceiver:LH80,SM1550
hpnicfevtPortSw-SGMII-100-BASE-LX-SFP      OBJECT IDENTIFIER ::= { hpnicfevtPortSwitchType 187 }  -- SGMII-100-BASE-LX-SFP Transceiver
hpnicfevtPortSw-SGMII-100-BASE-FX-SFP      OBJECT IDENTIFIER ::= { hpnicfevtPortSwitchType 188 }  -- SGMII-100-BASE-FX-SFP Transceiver
hpnicfevtPortSw-WLAN-RADIO                 OBJECT IDENTIFIER ::= { hpnicfevtPortSwitchType 189 }  -- WLAN-RADIO Transceiver
hpnicfevtPortSw-CABLE                      OBJECT IDENTIFIER ::= { hpnicfevtPortSwitchType 190 }  -- Cable Port
hpnicfevtPortSw-SFP-PLUS-NO-CONNECTOR      OBJECT IDENTIFIER ::= { hpnicfevtPortSwitchType 191 }  -- SFP+ without Transceiver
hpnicfevtPortSw-SFP-PLUS-10GBASE-SR        OBJECT IDENTIFIER ::= { hpnicfevtPortSwitchType 192 }  -- 10GBASE-SR SFP+ Transceiver
hpnicfevtPortSw-SFP-PLUS-10GBASE-LR        OBJECT IDENTIFIER ::= { hpnicfevtPortSwitchType 193 }  -- 10GBASE-LR SFP+ Transceiver
hpnicfevtPortSw-SFP-PLUS-10GBASE-LRM       OBJECT IDENTIFIER ::= { hpnicfevtPortSwitchType 194 }  -- 10GBASE-LRM SFP+ Transceiver
hpnicfevtPortSw-SFP-PLUS-10GBASE-Cu        OBJECT IDENTIFIER ::= { hpnicfevtPortSwitchType 195 }  -- 10GBASE-Cu SFP+ Transceiver
hpnicfevtPortSw-SFP-PLUS-UNKNOWN           OBJECT IDENTIFIER ::= { hpnicfevtPortSwitchType 196 }  -- Unknown SFP+ Transceiver
hpnicfevtPortSw-SFP-PLUS-STACK-CONNECTOR   OBJECT IDENTIFIER ::= { hpnicfevtPortSwitchType 197 }  -- SFP+ STACK Transceiver
hpnicfevtPortSw-POS-L-64-4                 OBJECT IDENTIFIER ::= { hpnicfevtPortSwitchType 198 }  -- STM64/OC192 Long Haul Fiber Optic Transceivers with LC Connector(wavelength 1550nm G.653 fiber)
hpnicfevtPortSw-MINISAS-HD-STACK-CONNECTOR OBJECT IDENTIFIER ::= { hpnicfevtPortSwitchType 199 }  -- MiniSAS HD STACK Transceiver
hpnicfevtPortSw-ONU-1000BASE-PX-SFF        OBJECT IDENTIFIER ::= { hpnicfevtPortSwitchType 200 }  -- 1000BASE-PX SFF ONU Interface
hpnicfevtPortSw-RS485                      OBJECT IDENTIFIER ::= { hpnicfevtPortSwitchType 201 }  -- RS-485 Interface
hpnicfevtPortSw-SFP-PLUS-10GBASE-ER        OBJECT IDENTIFIER ::= { hpnicfevtPortSwitchType 202 }  -- 10GBASE-ER SFP+ Transceiver
hpnicfevtPortSw-SFP-PLUS-10GBASE-ZR        OBJECT IDENTIFIER ::= { hpnicfevtPortSwitchType 203 }  -- 10GBASE-ZR SFP+ Transceiver
hpnicfevtPortSw-XFP-10GBASE-ZR             OBJECT IDENTIFIER ::= { hpnicfevtPortSwitchType 204 }  -- 10GBASE-ZR XFP Transceiver
hpnicfevtPortSw-QSFP-PLUS-40GBASE-SR4      OBJECT IDENTIFIER ::= { hpnicfevtPortSwitchType 205 }  -- 40BASE-SR4 QSFP+ Optical Transceiver
hpnicfevtPortSw-QSFP-PLUS-STACK-CONNECTOR  OBJECT IDENTIFIER ::= { hpnicfevtPortSwitchType 206 }  -- QSFP+ STACK Transceiver
hpnicfevtPortSw-QSFP-PLUS-TO-4SFP-PLUS-STACK-CONNECTOR OBJECT IDENTIFIER ::= { hpnicfevtPortSwitchType 207 }  -- QSFP+ to 4 SFP+ STACK Transceiver
hpnicfevtPortSw-SFP-STACK-CONNECTOR        OBJECT IDENTIFIER ::= { hpnicfevtPortSwitchType 208 }  -- SFP STACK Transceiver
hpnicfevtPortSw-QSFP-NO-CONNECTOR          OBJECT IDENTIFIER ::= { hpnicfevtPortSwitchType 209 }  -- QSFP No Connector
hpnicfevtPortSw-10GBase-T                  OBJECT IDENTIFIER ::= { hpnicfevtPortSwitchType 210 }  -- 10G Base-T Port
hpnicfevtPortSw-CFP-NO-CONNECTOR           OBJECT IDENTIFIER ::= { hpnicfevtPortSwitchType 211 }  -- CFP No Connector
hpnicfevtPortSw-CFP-40GBASE-LR4            OBJECT IDENTIFIER ::= { hpnicfevtPortSwitchType 212 }  -- 40GBASE-LR4 CFP Transceiver
hpnicfevtPortSw-QSFP-PLUS-NO-CONNECTOR     OBJECT IDENTIFIER ::= { hpnicfevtPortSwitchType 213 }  -- QSFP+ No Connector
hpnicfevtPortSw-QSFP-PLUS-40GBASE-LR4      OBJECT IDENTIFIER ::= { hpnicfevtPortSwitchType 214 }  -- 40GBASE-LR4 QSFP+ Optical Transceiver
hpnicfevtPortSw-CFP-40GBASE-SR4            OBJECT IDENTIFIER ::= { hpnicfevtPortSwitchType 215 }  -- 40GBASE-SR4 CFP Optical Transceiver
hpnicfevtPortSw-CFP-100GBASE-LR4           OBJECT IDENTIFIER ::= { hpnicfevtPortSwitchType 216 }  -- 100GBASE-LR4 CFP Optical Transceiver
hpnicfevtPortSw-CFP-100GBASE-SR10          OBJECT IDENTIFIER ::= { hpnicfevtPortSwitchType 217 }  -- 100GBASE-SR10 CFP Optical Transceiver
hpnicfevtPortSw-CXP-100GBASE-SR10          OBJECT IDENTIFIER ::= { hpnicfevtPortSwitchType 218 }  -- 100GBASE-SR10 CXP Optical Transceiver
hpnicfevtPortSw-CXP-NO-CONNECTOR           OBJECT IDENTIFIER ::= { hpnicfevtPortSwitchType 219 }  -- CXP No Connector
hpnicfevtPortSw-TRANSCEIVER-UNKNOWN        OBJECT IDENTIFIER ::= { hpnicfevtPortSwitchType 220 }  -- Unknown Transceiver
hpnicfevtPortSw-QSFP-PLUS-UNKNOWN          OBJECT IDENTIFIER ::= { hpnicfevtPortSwitchType 221 }  -- Unknown QSFP+ Transceiver
hpnicfevtPortSw-CFP-UNKNOWN                OBJECT IDENTIFIER ::= { hpnicfevtPortSwitchType 222 }  -- Unknown CFP Transceiver
hpnicfevtPortSw-QSFP-PLUS-40GBASE-CSR4     OBJECT IDENTIFIER ::= { hpnicfevtPortSwitchType 223 }  -- 40GBASE-CSR4 QSFP+ Optical Transceiver
hpnicfevtPortSw-CFP-40GBASE-ER4            OBJECT IDENTIFIER ::= { hpnicfevtPortSwitchType 224 }  -- 40GBASE-ER4 CFP Optical Transceiver
hpnicfevtPortSw-SFP-1000BASE-BIDI          OBJECT IDENTIFIER ::= { hpnicfevtPortSwitchType 225 }  -- 1000BASE SFP Bi-direction Optical Transceiver
hpnicfevtPortSw-SFP-PLUS-10GBASE-ZR-DWDM   OBJECT IDENTIFIER ::= { hpnicfevtPortSwitchType 226 }  -- 10GBase-ZR SFP+ DWDM Optical Transceiver
hpnicfevtPortSw-QSFP-PLUS-40GBASE-PSM      OBJECT IDENTIFIER ::= { hpnicfevtPortSwitchType 227 }  -- 40GBASE QSFP+ Parallel SingleMode Optical Transceiver
hpnicfevtPortSw-SFP-8GFC-SW                OBJECT IDENTIFIER ::= { hpnicfevtPortSwitchType 228 }  -- SFP 8G FC Optical Transceiver short wave
hpnicfevtPortSw-SFP-8GFC-LW                OBJECT IDENTIFIER ::= { hpnicfevtPortSwitchType 229 }  -- SFP 8G FC Optical Transceiver long wave
hpnicfevtPortSw-CXP-100GBASE-AOC           OBJECT IDENTIFIER ::= { hpnicfevtPortSwitchType 230 }  -- 100GBASE CXP Active Optical Cable
hpnicfevtPortSw-QSFP-PLUS-ACTIVE-STACK-CONNECTOR  OBJECT IDENTIFIER ::= { hpnicfevtPortSwitchType 231 }  -- QSFP+ Active STACK Transceiver
hpnicfevtPortSw-QSFP-PLUS-TO-4SFP-PLUS-ACTIVE-STACK-CONNECTOR  OBJECT IDENTIFIER ::= { hpnicfevtPortSwitchType 232 }  -- QSFP+ to 4 SFP+ Active STACK Transceiver


--
-- hpnicfevtStack section:
--
hpnicfevtStack     OBJECT IDENTIFIER ::= { hpnicfEntityVendortypeObjects 11 }


END
