--
-- ALBALA-MIB.my
-- MIB generated byWeekOfMonth
--

	ALBALA-MIB DEFINITIONS ::= BEGIN
 
		IMPORTS
			OBJECT-GROUP, NOTIFICATION-GROUP			
				FROM SNMPv2-CONF			
			enterprises, Integer32, OBJECT-TYPE, MODULE-IDENTITY, OBJECT-IDENTITY, 
			NOTIFICATION-TYPE			
				FROM SNMPv2-SMI			
			TEXTUAL-CONVENTION			
				FROM SNMPv2-TC;
	
	
		-- 1.3.6.1.4.1.10106.1.1.1
		albalaGlobalModule MODULE-IDENTITY 
			LAST-UPDATED "202205041214Z" -- May 4, 2022 at 12:14 GMT
			ORGANIZATION 
				"Albala Ingenieros, S.A."
			CONTACT-INFO 
				"Javier Hernadez , jmhm@albalaing.es"
			DESCRIPTION 
				"Definitions for Albala Ingenieros' products."
			REVISION "202205041214Z" -- May 4, 2022 at 12:14 GMT
			DESCRIPTION 
				"MIB Modules Albala"
			::= { albalaModules 1 }

		
	
--
-- Textual conventions
--
	
		AgentSts ::= TEXTUAL-CONVENTION
			STATUS current
			DESCRIPTION 
				"Description."
			SYNTAX INTEGER
				{
				disconected(0),
				connected(1),
				unlicenced(2)
				}


		AlarmEnable ::= TEXTUAL-CONVENTION
			STATUS current
			DESCRIPTION 
				"Trap enable for a status signal."
			SYNTAX INTEGER
				{
				no(0),
				yes(1)
				}

		ModuleIndex ::= TEXTUAL-CONVENTION
			STATUS current
			DESCRIPTION 
				"Position in chasis "
			SYNTAX INTEGER (1..14)

		ModuleStatus ::= TEXTUAL-CONVENTION
			STATUS current
			DESCRIPTION 
				"Description."
			SYNTAX INTEGER
				{
				empty(-4),
				unknown(-3),
				invalid(-2),
				error(-1),
				ok(0)
				}
	                        

		ModuleType ::= TEXTUAL-CONVENTION
			STATUS current
			DESCRIPTION
				"Modules types Albala"
			SYNTAX INTEGER
				{
				none(0),
				dvp3222p01v1(89101),
				vct3000p01v1(125101),
				vct3000c02v1(126001),
				vct3000c04v1(126201),
				vct3000c05v1(126301),
				dvm3000p01v1(128301),
				tpg3000p01v1(128701),
				dsw3000p01v1(129101),
				lns3000p01v1(130101),
				dli3000p01v2(131502),
				tly3032p01v1(133501),
				tly3016p01v1(133901),
				aac3000p01v1(134801),
				aem3000p01v1(134901),
				ade3000p01v1(135801),
				dsw3000c02v1(136301),
				dem3000p01v1(136601),
				dde3000p01v1(137101),
				avp0621p01v1(137701),
				aad3034p01v1(139701),
				avp1221p01v1(140401),
				aap1221p01v1(140801),
				frs3000p01v1(141201),
				pds3000p01v1(141701),
				avp1222p01v1(143301),
				aap0622p01v1(145201),
				avp0622p01v1(145601),
				aad3024p01v1(147801),
				aad3014p01v1(147901),
				aad3014c01v2(147902),
				aap0621p01v1(148001),
				aap1222p01v1(148101),
				sct3000c02v1(149301),
				dat3000p01v1(150501),
				cav3000p01v1(157401),
				cav3001p01v1(157501),
				cav3002p01v1(157601),
				dsw3000c03v1(162801),
				eap3000p01v1(163501),
				txe3000p01v1(166801),
				txe3000p01v2(166802),
				txd3000p01v1(166901),
				txd3000p01v2(166902),
				vfd3000c01v1(167201),
				dar3000p01v1(167501),
				txt3000p01v1(184801),
				dvp3224p01v1(187601),
				gps3000p01v1(195701),
				gps3000p01v2(195702),
				gps3000p01v3(195703),
				gps3000p01v4(195704),
				sdt3000p01v1(207201),
				sdr3000p01v1(207301),
				dsw3000p05v1(211201),
				gps3000p02v1(213201),
				gps3000p02v2(213202),
				gps3000p02v3(213203),
				gps3000p02v4(213204),
				pds3001p01v1(215401),
				gps3000p03v1(216401),
				gps3000p03v2(216402),
				gps3000p03v3(216403),
				gps3000p03v4(216404),
				frs3004c02v1(224701),
				kbd3100p01v1(226401),
				dvd3001p01v1(229601),
				frs3004c01v1(232401),
				dvd3001c02v1(233401),
				dvd3001c03v1(233501),
				dvd3001c04v1(234101),
				dvd3001c05v1(234201),
				sdr3000p02v1(238701),
				asw3000c01v1(241501),
				adl3000c01v1(245601),
				hvd3000c01v1(247001),
				hvd3000c01v2(247002),
				hdt3000c01v1(247101),
				hdr3000c01v1(247201),
				dli3001c01v1(259501),
				eap3001c01v1(259601),
				ur-3100r05v1(272801),
				ur-3100r06v1(272901),
				ur-3100r07v1(273001),
				ur-3100r08v1(273101),
				ur-3100r09v1(273201),
				dvm3001c01v1(274401),
				dsw3001c01v1(275101),
				dvb3001c01v1(278601),
				dvm3001c02v1(282401),
				dvb3001c02v1(283901),
				gps3002c01v1(286201),
				gps3002c03v1(290701),
				tsm3001c01v1(290901),
				tpg3001c01v1(295301),
				aac3008c01v1(308701),
				dsw3000c05v1(315301),
				ssw3000c01v1(316801),
				pdc3002c01v1(320501),
				vct3000c11v1(324201),
				vct3000c12v1(324301),
				vct3000c14v1(324401),
				vct3000c15v1(324501),
				vtl3000c01v1(327001),
				tle3001c01v1(328401),
				gvd3000c01v1(339901),
				htg3000c01v1(343901),
				hvd3001c01v1(347601),
				vct3000c13v1(350401),
				dad3002c02v1(352201),
				hvd3001c02v1(353101),
				hvd3001c03v1(357101),
				hvd3001c04v1(357201),
				hfs3000c01v1(357501),
				hfs3000c01v2(357502),
				hde3000c01v1(358101),
				hae3000c01v1(359901),
				had3000c01v1(360001),
				ipa3000c01v1(362001),
				ipa3000c01v2(362002),
				hsw3000c01v1(364801),
				hsw3000c01v2(364802),
				hsw3000c01v3(364803),
				eop0020c01v1(371701),
				hop3147c01v1(373501),
				hvp3000c01v1(375001),
				tle0001c01v1(376001),
				hdc3000c01v1(378901),
				hli3000c01v1(379801),
				hli3000c01v2(379802),
				eop0010c01v1(380001),
				hap3000c01v1(382501),
				hap3000c01v2(382502),
				psu3300c01v1(386801),
				psu3300c02v1(388901),
				psu3301c01v1(389201),
				psu3301c03v1(389501),
				avd3001c02v1(392001),
				avd3001c01v1(393601),
				avd3001c03v1(393701),
				vgp3000c01v1(399601),
				ham3000c01v1(403001),
				agw3000c01v1(404701),
				agw3000c01v2(404702),
				ham3000c02v1(407601),
				ham3000c03v1(407701),
				hop3147c02v1(412201),
				kbd3160c01v1(413901),
				act3000c01v1(415501),
				hvd2000c01v1(416301),
				kbd3160c02v1(420401),
				tsa3000c01v1(422601),
				tle2001c01v1(432201),
				psu2000c02v1(436601),
				eop2000c01v1(437801),
				avd2001c01v1(438701),
				hdc2000c01v1(442301),
				gps3002c04v1(442701),
				cws2016c01v1(443601),
				hdc2000c02v1(445101),
				hxc3000c01v1(446901),
				hsw2000c01v1(454401),
				htg2000c01v1(454501),
				htg2000c01v2(454502),
				aad2000c01v1(456201),
				aad2000c02v1(460201),
				aad2000c03v1(460301),
				aad2000c04v1(460401),
				ipa2000c01v1(461001),
				tle2001c02v1(467901),
				ddf2008c01v1(469001),
				hfs2000c01v1(470001),
				htc3000c01v1(471001),
				tle3001c02v1(473501),
				adf2008c01v1(474701),
				daf2008c01v1(474801),
				tly3032c04v1(478401),
				tle0001c02v1(478901),
				udp2000c01v1(483501),
				aem2008c01v1(484901),
				ade2008c01v1(485001),
				htg3001c01v1(485901),
				psu3300c03v1(494401),
				ttd3000c03v1(496001),
				adb2008c01v1(497501),
				dab2008c01v1(497601),
				ddb2008c01v1(497701),
				smc2000c01v1(514901),
				gps2000c01v1(517501),
				isw3000c01v1(520301),
				isw3000c01v2(520302),
				imb2000c01v1(522601),
				swc2000c01v1(523601),
				psu2001c01v1(524101),
				eol2000c01v1(527201),
				ttd2000c01v1(529001),
				psu2100c01v1(530801),
				atg2000c01v1(538901),
				hvd2001c01v1(540801),
				gti2000c01v1(542501),
				ste2022c01v1(550001),
				tly2010c01v1(552801),
				hli2000c01v1(553101),
				vct2000c01v1(553901),
				hxc2000c01v1(554501),
				uop2000c01v1(555601),
				ur-2001r01v1(557901),
				act2000c01v1(574401),
				utg2000c01v1(577901),
				hvd2002c01v1(579101),
				hfs2001c01v1(583701),
				gps3003c01v1(586701),
				sem2000c01v1(586801),
				gps3003c02v1(587301),
				gps3003c03v1(587501),
				gps3003c04v1(587701),
				ase2008c01v1(592801),
				aip2000c01v1(592901),
				asd2008c01v1(593001),
				ded2008c01v1(599301),
				uvd2000c01v1(600801),
				deb2008c01v1(607801),
				def2008c01v1(607901),
				dad2000c01v1(609201),
				vtr2000c01v1(612801),
				gpd2000c01v1(616301),
				hxc2000c02v1(620401),
				mpx2000c01v1(623301),
				rfa2018c01v1(627101)
				}

		ActGpoState ::= TEXTUAL-CONVENTION
			STATUS current
			DESCRIPTION
				"Type ACT_GPO_STATE"
			SYNTAX INTEGER
				{
				unknown(-3),
				inactive-inactive(0),
				inactive-active(1),
				active-inactive(2),
				active-active(3)
				}

		ActMapState ::= TEXTUAL-CONVENTION
			STATUS current
			DESCRIPTION
				"Type ACT_MAP_STATE"
			SYNTAX INTEGER
				{
				unknown(-3),
				in1(0),
				in2(1)
				}

		ActSwMode ::= TEXTUAL-CONVENTION
			STATUS current
			DESCRIPTION
				"Type ACT_SW_MODE"
			SYNTAX INTEGER
				{
				unknown(-3),
				full-auto(0),
				half-auto(1),
				manual(2),
				gpi(3)
				}

		AdbDabSlot ::= TEXTUAL-CONVENTION
			STATUS current
			DESCRIPTION
				"Type ADB_DAB_SLOT"
			SYNTAX INTEGER
				{
				unknown(-3),
				sel1(0),
				sel2(1),
				sel3(2),
				sel4(3),
				sel5(4),
				sel6(5),
				sel7(6),
				sel8(7),
				none(8)
				}

		AesMxInput1 ::= TEXTUAL-CONVENTION
			STATUS current
			DESCRIPTION
				"Type AES_MX_INPUT_1"
			SYNTAX INTEGER
				{
				unknown(-3),
				aes1-cha(0),
				aes1-chb(1),
				aes2-cha(2),
				aes2-chb(3)
				}

		Aes67Discovery ::= TEXTUAL-CONVENTION
			STATUS current
			DESCRIPTION
				"Type AES67_DISCOVERY"
			SYNTAX INTEGER
				{
				unknown(-3),
				disabled(0),
				sap(1),
				dns-sd(2),
				sapordns-sd(3)
				}

		Afd1 ::= TEXTUAL-CONVENTION
			STATUS current
			DESCRIPTION
				"Type AFD_1"
			SYNTAX INTEGER
				{
				unknown(-3),
				full-frame(0),
				sel4-3-centered(1),
				sel16-9-centered(2),
				unsupported(3)
				}

		AfdInfo ::= TEXTUAL-CONVENTION
			STATUS current
			DESCRIPTION
				"Type AFD_INFO"
			SYNTAX INTEGER
				{
				unknown(-3),
				not-present(0),
				not-defined(1),
				ar4-3-afd4-3ff(2),
				ar4-3-afd16-9c(3),
				ar4-3-afdother(4),
				ar16-9-afd4-3c(5),
				ar16-9-afd16-9ff(6),
				ar16-9-afdother(7)
				}

		AltitudeM1 ::= TEXTUAL-CONVENTION
			STATUS current
			DESCRIPTION
				"Type ALTITUDE_M_1"
			SYNTAX INTEGER
				{
				unknown(-3),
				range-min(0),
				range-max(65535)
				}

		AnaMxInput1 ::= TEXTUAL-CONVENTION
			STATUS current
			DESCRIPTION
				"Type ANA_MX_INPUT_1"
			SYNTAX INTEGER
				{
				unknown(-3),
				in1-cha(0),
				in1-chb(1),
				in2-cha(2),
				in2-chb(3)
				}

		AncInserterRep ::= TEXTUAL-CONVENTION
			STATUS current
			DESCRIPTION
				"Type ANC_INSERTER_REP"
			SYNTAX INTEGER
				{
				unknown(-3),
				range-min(0),
				range-max(255)
				}

		AngleDeg1 ::= TEXTUAL-CONVENTION
			STATUS current
			DESCRIPTION
				"Type ANGLE_DEG_1"
			SYNTAX INTEGER
				{
				unknown(-3),
				range-min(0),
				range-max(2147483647)
				}

		AtgMuxSrc ::= TEXTUAL-CONVENTION
			STATUS current
			DESCRIPTION
				"Type ATG_MUX_SRC"
			SYNTAX INTEGER
				{
				unknown(-3),
				w482(0),
				afnor87500oririg-b(1)
				}

		Att0dbInf ::= TEXTUAL-CONVENTION
			STATUS current
			DESCRIPTION
				"Type ATT_0DB_INF"
			SYNTAX INTEGER
				{
				unknown(-3),
				range-min(0),
				range-max(79)
				}

		AudioChannels ::= TEXTUAL-CONVENTION
			STATUS current
			DESCRIPTION
				"Type AUDIO_CHANNELS"
			SYNTAX INTEGER
				{
				unknown(-3),
				sel1-8(0),
				sel9-16(1),
				sel17-24(2),
				sel25-32(3)
				}

		AudioChannels2 ::= TEXTUAL-CONVENTION
			STATUS current
			DESCRIPTION
				"Type AUDIO_CHANNELS_2"
			SYNTAX INTEGER
				{
				unknown(-3),
				sel1-8(0),
				sel9-16(1),
				all(2)
				}

		AudioChannels3 ::= TEXTUAL-CONVENTION
			STATUS current
			DESCRIPTION
				"Type AUDIO_CHANNELS_3"
			SYNTAX INTEGER
				{
				unknown(-3),
				sel8-channels(0),
				sel16-channels(1)
				}

		AudioFailMode ::= TEXTUAL-CONVENTION
			STATUS current
			DESCRIPTION
				"Type AUDIO_FAIL_MODE"
			SYNTAX INTEGER
				{
				unknown(-3),
				no-signal(0),
				aes-silence(1)
				}

		AudioFreq1 ::= TEXTUAL-CONVENTION
			STATUS current
			DESCRIPTION
				"Type AUDIO_FREQ_1"
			SYNTAX INTEGER
				{
				unknown(-3),
				sel1-khz(0),
				sel400-hz(1)
				}

		AudioFreq2 ::= TEXTUAL-CONVENTION
			STATUS current
			DESCRIPTION
				"Type AUDIO_FREQ_2"
			SYNTAX INTEGER
				{
				unknown(-3),
				sel500-hz(0),
				sel1-khz(1),
				sel2-khz(2),
				sel4-khz(3)
				}

		AudioLev0 ::= TEXTUAL-CONVENTION
			STATUS current
			DESCRIPTION
				"Type AUDIO_LEV_0"
			SYNTAX INTEGER
				{
				unknown(-3),
				sel0-dbfs(0),
				sel-18-dbfs(1),
				sel-20-dbfs(2),
				silence(3)
				}

		AudioMask ::= TEXTUAL-CONVENTION
			STATUS current
			DESCRIPTION
				"Type AUDIO_MASK"
			SYNTAX INTEGER
				{
				unknown(-3),
				disabled(0),
				only-pres(1),
				pres-overld(2),
				enabled(3)
				}

		AudioMxIn5b ::= TEXTUAL-CONVENTION
			STATUS current
			DESCRIPTION
				"Type AUDIO_MX_IN_5B"
			SYNTAX INTEGER
				{
				unknown(-3),
				gr1p0(0),
				gr1p1(1),
				gr2p0(2),
				gr2p1(3),
				gr3p0(4),
				gr3p1(5),
				gr4p0(6),
				gr4p1(7)
				}

		AudioMxInput1 ::= TEXTUAL-CONVENTION
			STATUS current
			DESCRIPTION
				"Type AUDIO_MX_INPUT_1"
			SYNTAX INTEGER
				{
				unknown(-3),
				gr1p0a(0),
				gr1p1a(1),
				gr2p0a(2),
				gr2p1a(3),
				gr3p0a(4),
				gr3p1a(5),
				gr4p0a(6),
				gr4p1a(7),
				gr1p0b(8),
				gr1p1b(9),
				gr2p0b(10),
				gr2p1b(11),
				gr3p0b(12),
				gr3p1b(13),
				gr4p0b(14),
				gr4p1b(15),
				aes1a(16),
				aes2a(17),
				aes3a(18),
				aes4a(19),
				aes1b(20),
				aes2b(21),
				aes3b(22),
				aes4b(23),
				none(25)
				}

		AudioMxInput2 ::= TEXTUAL-CONVENTION
			STATUS current
			DESCRIPTION
				"Type AUDIO_MX_INPUT_2"
			SYNTAX INTEGER
				{
				unknown(-3),
				gr1p0a(0),
				gr1p1a(1),
				gr2p0a(2),
				gr2p1a(3),
				gr3p0a(4),
				gr3p1a(5),
				gr4p0a(6),
				gr4p1a(7),
				gr1p0b(8),
				gr1p1b(9),
				gr2p0b(10),
				gr2p1b(11),
				gr3p0b(12),
				gr3p1b(13),
				gr4p0b(14),
				gr4p1b(15),
				dars(26),
				none(25)
				}

		AudioMxInput3 ::= TEXTUAL-CONVENTION
			STATUS current
			DESCRIPTION
				"Type AUDIO_MX_INPUT_3"
			SYNTAX INTEGER
				{
				unknown(-3),
				gr1p0a(0),
				gr1p1a(1),
				gr2p0a(2),
				gr2p1a(3),
				gr3p0a(4),
				gr3p1a(5),
				gr4p0a(6),
				gr4p1a(7),
				gr1p0b(8),
				gr1p1b(9),
				gr2p0b(10),
				gr2p1b(11),
				gr3p0b(12),
				gr3p1b(13),
				gr4p0b(14),
				gr4p1b(15),
				strm1a(16),
				strm2a(17),
				strm1b(20),
				strm2b(21),
				none(25)
				}

		AudioMxInput4 ::= TEXTUAL-CONVENTION
			STATUS current
			DESCRIPTION
				"Type AUDIO_MX_INPUT_4"
			SYNTAX INTEGER
				{
				unknown(-3),
				gr1p0a(0),
				gr1p1a(1),
				gr2p0a(2),
				gr2p1a(3),
				gr3p0a(4),
				gr3p1a(5),
				gr4p0a(6),
				gr4p1a(7),
				gr1p0b(8),
				gr1p1b(9),
				gr2p0b(10),
				gr2p1b(11),
				gr3p0b(12),
				gr3p1b(13),
				gr4p0b(14),
				gr4p1b(15),
				none(25)
				}

		AudioMxInput5 ::= TEXTUAL-CONVENTION
			STATUS current
			DESCRIPTION
				"Type AUDIO_MX_INPUT_5"
			SYNTAX INTEGER
				{
				unknown(-3),
				gr1p0(0),
				gr1p1(1),
				gr2p0(2),
				gr2p1(3),
				gr3p0(4),
				gr3p1(5),
				gr4p0(6),
				gr4p1(7),
				none(8)
				}

		AudioMxInput6 ::= TEXTUAL-CONVENTION
			STATUS current
			DESCRIPTION
				"Type AUDIO_MX_INPUT_6"
			SYNTAX INTEGER
				{
				unknown(-3),
				gr1p0l(0),
				gr1p0r(1),
				gr1p1l(2),
				gr1p1r(3),
				gr2p0l(4),
				gr2p0r(5),
				gr2p1l(6),
				gr2p1r(7),
				gr3p0l(8),
				gr3p0r(9),
				gr3p1l(10),
				gr3p1r(11),
				gr4p0l(12),
				gr4p0r(13),
				gr4p1l(14),
				gr4p1r(15)
				}

		AudioMxInput7 ::= TEXTUAL-CONVENTION
			STATUS current
			DESCRIPTION
				"Type AUDIO_MX_INPUT_7"
			SYNTAX INTEGER
				{
				unknown(-3),
				range-min(0),
				range-max(15)
				}

		AudioMxInputA ::= TEXTUAL-CONVENTION
			STATUS current
			DESCRIPTION
				"Type AUDIO_MX_INPUT_A"
			SYNTAX INTEGER
				{
				unknown(-3),
				g1p0l(0),
				g1p0r(1),
				g1p1l(2),
				g1p1r(3),
				g2p0l(4),
				g2p0r(5),
				g2p1l(6),
				g2p1r(7),
				g3p0l(8),
				g3p0r(9),
				g3p1l(10),
				g3p1r(11),
				g4p0l(12),
				g4p0r(13),
				g4p1l(14),
				g4p1r(15),
				c1-a(16),
				c2-a(17),
				c3-a(18),
				c4-a(19),
				aes1l(20),
				aes1r(21),
				aes2l(22),
				aes2r(23),
				gen1(24),
				gen2(25),
				none(26)
				}

		AudioMxInputB ::= TEXTUAL-CONVENTION
			STATUS current
			DESCRIPTION
				"Type AUDIO_MX_INPUT_B"
			SYNTAX INTEGER
				{
				unknown(-3),
				g1p0(0),
				g1p0r(1),
				g1p1(2),
				g1p1r(3),
				g2p0(4),
				g2p0r(5),
				g2p1(6),
				g2p1r(7),
				g3p0(8),
				g3p0r(9),
				g3p1(10),
				g3p1r(11),
				g4p0(12),
				g4p0r(13),
				g4p1(14),
				g4p1r(15),
				c1a(16),
				c2a(17),
				c3a(18),
				c4a(19),
				aes1l(20),
				aes1r(21),
				aes2l(22),
				aes2r(23),
				gn1(24),
				gn2(25),
				an1l(26),
				an1r(27),
				an2l(28),
				an2r(29),
				none(30)
				}

		AudioRef1 ::= TEXTUAL-CONVENTION
			STATUS current
			DESCRIPTION
				"Type AUDIO_REF_1"
			SYNTAX INTEGER
				{
				unknown(-3),
				aes(0),
				bb-525(1),
				bb-625(2),
				wclk(3)
				}

		AudioRef2 ::= TEXTUAL-CONVENTION
			STATUS current
			DESCRIPTION
				"Type AUDIO_REF_2"
			SYNTAX INTEGER
				{
				unknown(-3),
				none(0),
				bb-625(1),
				bb-525(2),
				wclk(3),
				aes(4)
				}

		AudioRef3 ::= TEXTUAL-CONVENTION
			STATUS current
			DESCRIPTION
				"Type AUDIO_REF_3"
			SYNTAX INTEGER
				{
				unknown(-3),
				wclk(0),
				bb-525(1),
				bb-625(2),
				aes11(3)
				}

		AudioRef4 ::= TEXTUAL-CONVENTION
			STATUS current
			DESCRIPTION
				"Type AUDIO_REF_4"
			SYNTAX INTEGER
				{
				unknown(-3),
				aes(0),
				bb-625(1),
				bb-525(2),
				wclk(3)
				}

		AudioSelFreq1 ::= TEXTUAL-CONVENTION
			STATUS current
			DESCRIPTION
				"Type AUDIO_SEL_FREQ_1"
			SYNTAX INTEGER
				{
				unknown(-3),
				sel32-khz(0),
				sel44dot1-khz(1),
				sel48-khz(2),
				sel64-khz(3),
				sel88dot2-khz(4),
				sel96-khz(5),
				undefined(6),
				varispeed(7)
				}

		AudioSelFreq2 ::= TEXTUAL-CONVENTION
			STATUS current
			DESCRIPTION
				"Type AUDIO_SEL_FREQ_2"
			SYNTAX INTEGER
				{
				unknown(-3),
				sel32-khz(1),
				sel44dot1-khz(2),
				sel48-khz(3),
				sel64-khz(4),
				sel88dot2-khz(5),
				sel96-khz(6)
				}

		AudioSelFreq3 ::= TEXTUAL-CONVENTION
			STATUS current
			DESCRIPTION
				"Type AUDIO_SEL_FREQ_3"
			SYNTAX INTEGER
				{
				unknown(-3),
				no-signal-or-less32-khz(0),
				sel32-khz(1),
				sel44dot1-khz(2),
				sel48-khz(3),
				sel64-khz(4),
				sel88dot2-khz(5),
				sel96-khz(6),
				other-or-greater96-khz(7)
				}

		AudioSelFreq4 ::= TEXTUAL-CONVENTION
			STATUS current
			DESCRIPTION
				"Type AUDIO_SEL_FREQ_4"
			SYNTAX INTEGER
				{
				unknown(-3),
				sel32-khz(0),
				sel44dot1-khz(1),
				sel48-khz(2),
				sel64-khz(3),
				sel88dot2-khz(4),
				sel96-khz(5),
				other(6),
				no-signal(7)
				}

		AudioSelFreq5 ::= TEXTUAL-CONVENTION
			STATUS current
			DESCRIPTION
				"Type AUDIO_SEL_FREQ_5"
			SYNTAX INTEGER
				{
				unknown(-3),
				varispeed(0),
				sel48-khz-free-run(1),
				sel96-khz(2),
				sel88dot2-khz(3),
				sel64-khz(4),
				sel48-khz(5),
				sel44dot1-khz(6),
				sel32-khz(7)
				}

		AudioSelFreq6 ::= TEXTUAL-CONVENTION
			STATUS current
			DESCRIPTION
				"Type AUDIO_SEL_FREQ_6"
			SYNTAX INTEGER
				{
				unknown(-3),
				unknown0(0),
				sel32-khz(1),
				sel44dot1-khz(2),
				sel48-khz(3),
				sel64-khz(4),
				sel88dot2-khz(5),
				sel96-khz(6),
				unknown7(7)
				}

		AudioSelFreq7 ::= TEXTUAL-CONVENTION
			STATUS current
			DESCRIPTION
				"Type AUDIO_SEL_FREQ_7"
			SYNTAX INTEGER
				{
				unknown(-3),
				sel32-khz(0),
				sel44dot1-khz(1),
				sel48-khz(2),
				sel64-khz(3),
				sel88dot2-khz(4),
				sel96-khz(5)
				}

		AudioSource ::= TEXTUAL-CONVENTION
			STATUS current
			DESCRIPTION
				"Type AUDIO_SOURCE"
			SYNTAX INTEGER
				{
				unknown(-3),
				embedded(0),
				bus(1),
				silence(2),
				none(3)
				}

		AudioStatus ::= TEXTUAL-CONVENTION
			STATUS current
			DESCRIPTION
				"Type AUDIO_STATUS"
			SYNTAX INTEGER
				{
				unknown(-3),
				ok(0),
				ok-non-pcm(1),
				antiphase(2),
				silence-ch-a(3),
				silence-ch-b(4),
				silence-ch-a-b(5),
				sil-ch-a-ovld-ch-b(6),
				ovld-ch-a-sil-ch-b(7),
				overld-ch-a(8),
				overld-ch-b(9),
				overld-ch-a-b(10),
				not-known(14),
				fail(15)
				}

		AutosyncControl ::= TEXTUAL-CONVENTION
			STATUS current
			DESCRIPTION
				"Type AUTOSYNC_CONTROL"
			SYNTAX INTEGER
				{
				unknown(-3),
				ptp(0),
				autosync(1)
				}

		AutosyncMode ::= TEXTUAL-CONVENTION
			STATUS current
			DESCRIPTION
				"Type AUTOSYNC_MODE"
			SYNTAX INTEGER
				{
				unknown(-3),
				slave(0),
				master(1)
				}

		BgfBits ::= TEXTUAL-CONVENTION
			STATUS current
			DESCRIPTION
				"Type BGF_BITS"
			SYNTAX INTEGER
				{
				unknown(-3),
				ta-unspecdotorbg-unspecdot(0),
				ta-unspecdotorbg-8-bit-codot(1),
				ta-clkdottimeorbg-unspecdot(2),
				ta-reservedorbg-reserved(3),
				ta-unspecdotorbg-date-tdotzdot(4),
				ta-unspecdotorbg-page-line(5),
				ta-clkdottimeorbg-date-tdotzdot(6),
				ta-clkdottimeorbg-page-line(7)
				}

		Bit00db1Nxdb ::= TEXTUAL-CONVENTION
			STATUS current
			DESCRIPTION
				"Type BIT_0_0DB_1_NXDB"
			SYNTAX INTEGER
				{
				unknown(-3),
				sel0-dbfs(0),
				sel-18or-20-dbfs(1)
				}

		Bit01s1Total ::= TEXTUAL-CONVENTION
			STATUS current
			DESCRIPTION
				"Type BIT_0_1S_1_TOTAL"
			SYNTAX INTEGER
				{
				unknown(-3),
				sel1-s(0),
				total(1)
				}

		Bit0214 ::= TEXTUAL-CONVENTION
			STATUS current
			DESCRIPTION
				"Type BIT_0_2_1_4"
			SYNTAX INTEGER
				{
				unknown(-3),
				sel2(0),
				sel4(1)
				}

		Bit020124 ::= TEXTUAL-CONVENTION
			STATUS current
			DESCRIPTION
				"Type BIT_0_20_1_24"
			SYNTAX INTEGER
				{
				unknown(-3),
				sel20(0),
				sel24(1)
				}

		Bit02041188 ::= TEXTUAL-CONVENTION
			STATUS current
			DESCRIPTION
				"Type BIT_0_204_1_188"
			SYNTAX INTEGER
				{
				unknown(-3),
				sel204(0),
				sel188(1)
				}

		Bit024120 ::= TEXTUAL-CONVENTION
			STATUS current
			DESCRIPTION
				"Type BIT_0_24_1_20"
			SYNTAX INTEGER
				{
				unknown(-3),
				sel24(0),
				sel20(1)
				}

		Bit029fr125f ::= TEXTUAL-CONVENTION
			STATUS current
			DESCRIPTION
				"Type BIT_0_29FR_1_25F"
			SYNTAX INTEGER
				{
				unknown(-3),
				sel29dot97-frors(0),
				sel25-frors(1)
				}

		Bit0412 ::= TEXTUAL-CONVENTION
			STATUS current
			DESCRIPTION
				"Type BIT_0_4_1_2"
			SYNTAX INTEGER
				{
				unknown(-3),
				sel4(0),
				sel2(1)
				}

		Bit0481192 ::= TEXTUAL-CONVENTION
			STATUS current
			DESCRIPTION
				"Type BIT_0_48_1_192"
			SYNTAX INTEGER
				{
				unknown(-3),
				sel48-khz(0),
				sel192-khz(1)
				}

		Bit04851232 ::= TEXTUAL-CONVENTION
			STATUS current
			DESCRIPTION
				"Type BIT_0_485_1_232"
			SYNTAX INTEGER
				{
				unknown(-3),
				eia-rs485(0),
				eia-rs232(1)
				}

		Bit05251625 ::= TEXTUAL-CONVENTION
			STATUS current
			DESCRIPTION
				"Type BIT_0_525_1_625"
			SYNTAX INTEGER
				{
				unknown(-3),
				sel525(0),
				sel625(1)
				}

		Bit06251525 ::= TEXTUAL-CONVENTION
			STATUS current
			DESCRIPTION
				"Type BIT_0_625_1_525"
			SYNTAX INTEGER
				{
				unknown(-3),
				sel625(0),
				sel525(1)
				}

		Bit0Alrm1Sta ::= TEXTUAL-CONVENTION
			STATUS current
			DESCRIPTION
				"Type BIT_0_ALRM_1_STA"
			SYNTAX INTEGER
				{
				unknown(-3),
				alarm(0),
				state(1)
				}

		Bit0Ana1Dig ::= TEXTUAL-CONVENTION
			STATUS current
			DESCRIPTION
				"Type BIT_0_ANA_1_DIG"
			SYNTAX INTEGER
				{
				unknown(-3),
				analog(0),
				digital(1)
				}

		Bit0And1Or ::= TEXTUAL-CONVENTION
			STATUS current
			DESCRIPTION
				"Type BIT_0_AND_1_OR"
			SYNTAX INTEGER
				{
				unknown(-3),
				and(0),
				or(1)
				}

		Bit0Ann1For ::= TEXTUAL-CONVENTION
			STATUS current
			DESCRIPTION
				"Type BIT_0_ANN_1_FOR"
			SYNTAX INTEGER
				{
				unknown(-3),
				announced(0),
				forced(1)
				}

		Bit0Aut1Man ::= TEXTUAL-CONVENTION
			STATUS current
			DESCRIPTION
				"Type BIT_0_AUT_1_MAN"
			SYNTAX INTEGER
				{
				unknown(-3),
				auto(0),
				manual(1)
				}

		Bit0Aux1Pgm ::= TEXTUAL-CONVENTION
			STATUS current
			DESCRIPTION
				"Type BIT_0_AUX_1_PGM"
			SYNTAX INTEGER
				{
				unknown(-3),
				aux-in(0),
				pgm-in(1)
				}

		Bit0Blk1Nos ::= TEXTUAL-CONVENTION
			STATUS current
			DESCRIPTION
				"Type BIT_0_BLK_1_NOS"
			SYNTAX INTEGER
				{
				unknown(-3),
				black(0),
				no-signal(1)
				}

		Bit0Bnk1Pas ::= TEXTUAL-CONVENTION
			STATUS current
			DESCRIPTION
				"Type BIT_0_BNK_1_PAS"
			SYNTAX INTEGER
				{
				unknown(-3),
				blank(0),
				pass(1)
				}

		Bit0Cb1Bb ::= TEXTUAL-CONVENTION
			STATUS current
			DESCRIPTION
				"Type BIT_0_CB_1_BB"
			SYNTAX INTEGER
				{
				unknown(-3),
				colour-bars(0),
				black(1)
				}

		Bit0Ccvs1Bb ::= TEXTUAL-CONVENTION
			STATUS current
			DESCRIPTION
				"Type BIT_0_CCVS_1_BB"
			SYNTAX INTEGER
				{
				unknown(-3),
				ccvs-input(0),
				black-burst(1)
				}

		Bit0Chr1Lum ::= TEXTUAL-CONVENTION
			STATUS current
			DESCRIPTION
				"Type BIT_0_CHR_1_LUM"
			SYNTAX INTEGER
				{
				unknown(-3),
				chrominance(0),
				luminance(1)
				}

		Bit0Clo1Open ::= TEXTUAL-CONVENTION
			STATUS current
			DESCRIPTION
				"Type BIT_0_CLO_1_OPEN"
			SYNTAX INTEGER
				{
				unknown(-3),
				closed(0),
				open(1)
				}

		Bit0Clr1App ::= TEXTUAL-CONVENTION
			STATUS current
			DESCRIPTION
				"Type BIT_0_CLR_1_APP"
			SYNTAX INTEGER
				{
				unknown(-3),
				clear-insert(0),
				append(1)
				}

		Bit0Cus1Std ::= TEXTUAL-CONVENTION
			STATUS current
			DESCRIPTION
				"Type BIT_0_CUS_1_STD"
			SYNTAX INTEGER
				{
				unknown(-3),
				custom(0),
				standard(1)
				}

		Bit0Del1Syn ::= TEXTUAL-CONVENTION
			STATUS current
			DESCRIPTION
				"Type BIT_0_DEL_1_SYN"
			SYNTAX INTEGER
				{
				unknown(-3),
				delayer(0),
				synchronizer(1)
				}

		Bit0Dis1Ena ::= TEXTUAL-CONVENTION
			STATUS current
			DESCRIPTION
				"Type BIT_0_DIS_1_ENA"
			SYNTAX INTEGER
				{
				unknown(-3),
				disabled(0),
				enabled(1)
				}

		Bit0E11E3 ::= TEXTUAL-CONVENTION
			STATUS current
			DESCRIPTION
				"Type BIT_0_E1_1_E3"
			SYNTAX INTEGER
				{
				unknown(-3),
				e1(0),
				e3(1)
				}

		Bit0Ele1Opt ::= TEXTUAL-CONVENTION
			STATUS current
			DESCRIPTION
				"Type BIT_0_ELE_1_OPT"
			SYNTAX INTEGER
				{
				unknown(-3),
				electrical(0),
				optical(1)
				}

		Bit0Ena1Dis ::= TEXTUAL-CONVENTION
			STATUS current
			DESCRIPTION
				"Type BIT_0_ENA_1_DIS"
			SYNTAX INTEGER
				{
				unknown(-3),
				enabled(0),
				disabled(1)
				}

		Bit0Ext1Nor ::= TEXTUAL-CONVENTION
			STATUS current
			DESCRIPTION
				"Type BIT_0_EXT_1_NOR"
			SYNTAX INTEGER
				{
				unknown(-3),
				extended(0),
				normal(1)
				}

		Bit0Fld1Fra ::= TEXTUAL-CONVENTION
			STATUS current
			DESCRIPTION
				"Type BIT_0_FLD_1_FRA"
			SYNTAX INTEGER
				{
				unknown(-3),
				field(0),
				frame(1)
				}

		Bit0Flt1Not ::= TEXTUAL-CONVENTION
			STATUS current
			DESCRIPTION
				"Type BIT_0_FLT_1_NOT"
			SYNTAX INTEGER
				{
				unknown(-3),
				flat(0),
				notch(1)
				}

		Bit0Fra1Lin ::= TEXTUAL-CONVENTION
			STATUS current
			DESCRIPTION
				"Type BIT_0_FRA_1_LIN"
			SYNTAX INTEGER
				{
				unknown(-3),
				frame(0),
				line(1)
				}

		Bit0Fre1Blk ::= TEXTUAL-CONVENTION
			STATUS current
			DESCRIPTION
				"Type BIT_0_FRE_1_BLK"
			SYNTAX INTEGER
				{
				unknown(-3),
				freeze(0),
				black(1)
				}

		Bit0G7031Oth ::= TEXTUAL-CONVENTION
			STATUS current
			DESCRIPTION
				"Type BIT_0_G703_1_OTH"
			SYNTAX INTEGER
				{
				unknown(-3),
				g703(0),
				other(1)
				}

		Bit0Gpi1Bit ::= TEXTUAL-CONVENTION
			STATUS current
			DESCRIPTION
				"Type BIT_0_GPI_1_BIT"
			SYNTAX INTEGER
				{
				unknown(-3),
				gpi(0),
				bit(1)
				}

		Bit0Gpi1Reg ::= TEXTUAL-CONVENTION
			STATUS current
			DESCRIPTION
				"Type BIT_0_GPI_1_REG"
			SYNTAX INTEGER
				{
				unknown(-3),
				gpi(0),
				control-register(1)
				}

		Bit0Hd1Sd ::= TEXTUAL-CONVENTION
			STATUS current
			DESCRIPTION
				"Type BIT_0_HD_1_SD"
			SYNTAX INTEGER
				{
				unknown(-3),
				hd(0),
				sd(1)
				}

		Bit0Hrz1Av ::= TEXTUAL-CONVENTION
			STATUS current
			DESCRIPTION
				"Type BIT_0_HRZ_1_AV"
			SYNTAX INTEGER
				{
				unknown(-3),
				horiz-blank(0),
				active-video(1)
				}

		Bit0In1Out ::= TEXTUAL-CONVENTION
			STATUS current
			DESCRIPTION
				"Type BIT_0_IN_1_OUT"
			SYNTAX INTEGER
				{
				unknown(-3),
				in(0),
				out(1)
				}

		Bit0Ina1Act ::= TEXTUAL-CONVENTION
			STATUS current
			DESCRIPTION
				"Type BIT_0_INA_1_ACT"
			SYNTAX INTEGER
				{
				unknown(-3),
				inactive(0),
				active(1)
				}

		Bit0Ipm1Ipr ::= TEXTUAL-CONVENTION
			STATUS current
			DESCRIPTION
				"Type BIT_0_IPM_1_IPR"
			SYNTAX INTEGER
				{
				unknown(-3),
				ip-res-inp(0),
				ip-main-inp(1)
				}

		Bit0Lev1Edg ::= TEXTUAL-CONVENTION
			STATUS current
			DESCRIPTION
				"Type BIT_0_LEV_1_EDG"
			SYNTAX INTEGER
				{
				unknown(-3),
				level(0),
				edge(1)
				}

		Bit0Lin1Fra ::= TEXTUAL-CONVENTION
			STATUS current
			DESCRIPTION
				"Type BIT_0_LIN_1_FRA"
			SYNTAX INTEGER
				{
				unknown(-3),
				line(0),
				frame(1)
				}

		Bit0Man1Aut ::= TEXTUAL-CONVENTION
			STATUS current
			DESCRIPTION
				"Type BIT_0_MAN_1_AUT"
			SYNTAX INTEGER
				{
				unknown(-3),
				manual(0),
				auto(1)
				}

		Bit0N181N20 ::= TEXTUAL-CONVENTION
			STATUS current
			DESCRIPTION
				"Type BIT_0_N18_1_N20"
			SYNTAX INTEGER
				{
				unknown(-3),
				sel-18-dbfs(0),
				sel-20-dbfs(1)
				}

		Bit0Ndr1Drp ::= TEXTUAL-CONVENTION
			STATUS current
			DESCRIPTION
				"Type BIT_0_NDR_1_DRP"
			SYNTAX INTEGER
				{
				unknown(-3),
				no-drop(0),
				drop(1)
				}

		Bit0No1Yes ::= TEXTUAL-CONVENTION
			STATUS current
			DESCRIPTION
				"Type BIT_0_NO_1_YES"
			SYNTAX INTEGER
				{
				unknown(-3),
				no(0),
				yes(1)
				}

		Bit0Nor1Inv ::= TEXTUAL-CONVENTION
			STATUS current
			DESCRIPTION
				"Type BIT_0_NOR_1_INV"
			SYNTAX INTEGER
				{
				unknown(-3),
				normal(0),
				inverted(1)
				}

		Bit0Nos1Tes ::= TEXTUAL-CONVENTION
			STATUS current
			DESCRIPTION
				"Type BIT_0_NOS_1_TES"
			SYNTAX INTEGER
				{
				unknown(-3),
				no-signal(0),
				test-signal(1)
				}

		Bit0Not1Flt ::= TEXTUAL-CONVENTION
			STATUS current
			DESCRIPTION
				"Type BIT_0_NOT_1_FLT"
			SYNTAX INTEGER
				{
				unknown(-3),
				notch(0),
				flat(1)
				}

		Bit0Off1On ::= TEXTUAL-CONVENTION
			STATUS current
			DESCRIPTION
				"Type BIT_0_OFF_1_ON"
			SYNTAX INTEGER
				{
				unknown(-3),
				off(0),
				on(1)
				}

		Bit0Ok1Fail ::= TEXTUAL-CONVENTION
			STATUS current
			DESCRIPTION
				"Type BIT_0_OK_1_FAIL"
			SYNTAX INTEGER
				{
				unknown(-3),
				ok(0),
				fail(1)
				}

		Bit0Open1Clo ::= TEXTUAL-CONVENTION
			STATUS current
			DESCRIPTION
				"Type BIT_0_OPEN_1_CLO"
			SYNTAX INTEGER
				{
				unknown(-3),
				open(0),
				closed(1)
				}

		Bit0Opt1Ele ::= TEXTUAL-CONVENTION
			STATUS current
			DESCRIPTION
				"Type BIT_0_OPT_1_ELE"
			SYNTAX INTEGER
				{
				unknown(-3),
				optical(0),
				electrical(1)
				}

		Bit0Out1In ::= TEXTUAL-CONVENTION
			STATUS current
			DESCRIPTION
				"Type BIT_0_OUT_1_IN"
			SYNTAX INTEGER
				{
				unknown(-3),
				out(0),
				in(1)
				}

		Bit0Pas1Bnk ::= TEXTUAL-CONVENTION
			STATUS current
			DESCRIPTION
				"Type BIT_0_PAS_1_BNK"
			SYNTAX INTEGER
				{
				unknown(-3),
				pass(0),
				blank(1)
				}

		Bit0Pass1Rem ::= TEXTUAL-CONVENTION
			STATUS current
			DESCRIPTION
				"Type BIT_0_PASS_1_REM"
			SYNTAX INTEGER
				{
				unknown(-3),
				preserve(0),
				remove(1)
				}

		Bit0Pck1Brs ::= TEXTUAL-CONVENTION
			STATUS current
			DESCRIPTION
				"Type BIT_0_PCK_1_BRS"
			SYNTAX INTEGER
				{
				unknown(-3),
				packet-mode(0),
				burst-mode(1)
				}

		Bit0Pips1Wav ::= TEXTUAL-CONVENTION
			STATUS current
			DESCRIPTION
				"Type BIT_0_PIPS_1_WAV"
			SYNTAX INTEGER
				{
				unknown(-3),
				pips(0),
				sinewave(1)
				}

		Bit0Pro1Syn ::= TEXTUAL-CONVENTION
			STATUS current
			DESCRIPTION
				"Type BIT_0_PRO_1_SYN"
			SYNTAX INTEGER
				{
				unknown(-3),
				video-processor(0),
				line-synchronizer(1)
				}

		Bit0Rgb1Ycr ::= TEXTUAL-CONVENTION
			STATUS current
			DESCRIPTION
				"Type BIT_0_RGB_1_YCR"
			SYNTAX INTEGER
				{
				unknown(-3),
				rgb(0),
				ycrcb(1)
				}

		Bit0Sd1Hd ::= TEXTUAL-CONVENTION
			STATUS current
			DESCRIPTION
				"Type BIT_0_SD_1_HD"
			SYNTAX INTEGER
				{
				unknown(-3),
				sd(0),
				hd(1)
				}

		Bit0Sea1Nse ::= TEXTUAL-CONVENTION
			STATUS current
			DESCRIPTION
				"Type BIT_0_SEA_1_NSE"
			SYNTAX INTEGER
				{
				unknown(-3),
				seamless(0),
				no-seamless(1)
				}

		Bit0Sin1Dua ::= TEXTUAL-CONVENTION
			STATUS current
			DESCRIPTION
				"Type BIT_0_SIN_1_DUA"
			SYNTAX INTEGER
				{
				unknown(-3),
				single(0),
				dual(1)
				}

		Bit0Ste1Mon ::= TEXTUAL-CONVENTION
			STATUS current
			DESCRIPTION
				"Type BIT_0_STE_1_MON"
			SYNTAX INTEGER
				{
				unknown(-3),
				stereo(0),
				mono(1)
				}

		Bit0Syn1De2 ::= TEXTUAL-CONVENTION
			STATUS current
			DESCRIPTION
				"Type BIT_0_SYN_1_DE_2"
			SYNTAX INTEGER
				{
				unknown(-3),
				synchronizer(0),
				delayer(1)
				}

		Bit0Syn1Del ::= TEXTUAL-CONVENTION
			STATUS current
			DESCRIPTION
				"Type BIT_0_SYN_1_DEL"
			SYNTAX INTEGER
				{
				unknown(-3),
				synchronizer-delayer(0),
				delayer(1)
				}

		Bit0Tra1Fix ::= TEXTUAL-CONVENTION
			STATUS current
			DESCRIPTION
				"Type BIT_0_TRA_1_FIX"
			SYNTAX INTEGER
				{
				unknown(-3),
				track(0),
				fix(1)
				}

		Bit0Trk1Hol ::= TEXTUAL-CONVENTION
			STATUS current
			DESCRIPTION
				"Type BIT_0_TRK_1_HOL"
			SYNTAX INTEGER
				{
				unknown(-3),
				tracking(0),
				holdover(1)
				}

		Bit0Ts1Mr ::= TEXTUAL-CONVENTION
			STATUS current
			DESCRIPTION
				"Type BIT_0_TS_1_MR"
			SYNTAX INTEGER
				{
				unknown(-3),
				test-signal-no-signal(0),
				main-reserve(1)
				}

		Bit0V21V3 ::= TEXTUAL-CONVENTION
			STATUS current
			DESCRIPTION
				"Type BIT_0_V2_1_V3"
			SYNTAX INTEGER
				{
				unknown(-3),
				v2(0),
				v3(1)
				}

		Bit0Vid1Ext ::= TEXTUAL-CONVENTION
			STATUS current
			DESCRIPTION
				"Type BIT_0_VID_1_EXT"
			SYNTAX INTEGER
				{
				unknown(-3),
				video(0),
				external(1)
				}

		Bit0Yes1No ::= TEXTUAL-CONVENTION
			STATUS current
			DESCRIPTION
				"Type BIT_0_YES_1_NO"
			SYNTAX INTEGER
				{
				unknown(-3),
				yes(0),
				no(1)
				}

		BitAct ::= TEXTUAL-CONVENTION
			STATUS current
			DESCRIPTION
				"Type BIT_ACT"
			SYNTAX INTEGER
				{
				unknown(-3),
				inactive(0),
				active(1)
				}

		BitDistrib1 ::= TEXTUAL-CONVENTION
			STATUS current
			DESCRIPTION
				"Type BIT_DISTRIB_1"
			SYNTAX INTEGER
				{
				unknown(-3),
				sel2x1-to-6(0),
				sel1x1-to-12(1)
				}

		BitEmbed1 ::= TEXTUAL-CONVENTION
			STATUS current
			DESCRIPTION
				"Type BIT_EMBED_1"
			SYNTAX INTEGER
				{
				unknown(-3),
				sel1sdi-2groups(0),
				sel2sdi-1group(1)
				}

		BitEthActivity ::= TEXTUAL-CONVENTION
			STATUS current
			DESCRIPTION
				"Type BIT_ETH_ACTIVITY"
			SYNTAX INTEGER
				{
				unknown(-3),
				sel0(0),
				sel1(1)
				}

		BitFail ::= TEXTUAL-CONVENTION
			STATUS current
			DESCRIPTION
				"Type BIT_FAIL"
			SYNTAX INTEGER
				{
				unknown(-3),
				ok(0),
				fail(1)
				}

		BitFailN ::= TEXTUAL-CONVENTION
			STATUS current
			DESCRIPTION
				"Type BIT_FAIL_N"
			SYNTAX INTEGER
				{
				unknown(-3),
				fail(0),
				ok(1)
				}

		BitMask ::= TEXTUAL-CONVENTION
			STATUS current
			DESCRIPTION
				"Type BIT_MASK"
			SYNTAX INTEGER
				{
				unknown(-3),
				disabled(0),
				enabled(1)
				}

		BitMultichnl ::= TEXTUAL-CONVENTION
			STATUS current
			DESCRIPTION
				"Type BIT_MULTICHNL"
			SYNTAX INTEGER
				{
				unknown(-3),
				normal(0),
				multichannel(1)
				}

		BitPps ::= TEXTUAL-CONVENTION
			STATUS current
			DESCRIPTION
				"Type BIT_PPS"
			SYNTAX INTEGER
				{
				unknown(-3),
				sel0(0),
				sel1(1)
				}

		Bit0BlBit1Cut ::= TEXTUAL-CONVENTION
			STATUS current
			DESCRIPTION
				"Type BIT0_BL_BIT1_CUT"
			SYNTAX INTEGER
				{
				unknown(-3),
				black(0),
				cut(1)
				}

		Bit0LdBit1Pk ::= TEXTUAL-CONVENTION
			STATUS current
			DESCRIPTION
				"Type BIT0_LD_BIT1_PK"
			SYNTAX INTEGER
				{
				unknown(-3),
				loudness(0),
				peak(1),
				gain(2)
				}

		Bit0LdBit1Pk2 ::= TEXTUAL-CONVENTION
			STATUS current
			DESCRIPTION
				"Type BIT0_LD_BIT1_PK2"
			SYNTAX INTEGER
				{
				unknown(-3),
				loudness(0),
				peak(1)
				}

		Bit0MBit1S ::= TEXTUAL-CONVENTION
			STATUS current
			DESCRIPTION
				"Type BIT0_M_BIT1_S"
			SYNTAX INTEGER
				{
				unknown(-3),
				momentary(0),
				short-term(1)
				}

		Bit0Pos1Neg ::= TEXTUAL-CONVENTION
			STATUS current
			DESCRIPTION
				"Type BIT0_POS_1_NEG"
			SYNTAX INTEGER
				{
				unknown(-3),
				positive(0),
				negative(1)
				}

		Bitrate ::= TEXTUAL-CONVENTION
			STATUS current
			DESCRIPTION
				"Type BITRATE"
			SYNTAX INTEGER
				{
				unknown(-3),
				range-min(0),
				range-max(16777215)
				}

		Bitrate2kbps ::= TEXTUAL-CONVENTION
			STATUS current
			DESCRIPTION
				"Type BITRATE_2KBPS"
			SYNTAX INTEGER
				{
				unknown(-3),
				range-min(0),
				range-max(65535)
				}

		BitrateControl ::= TEXTUAL-CONVENTION
			STATUS current
			DESCRIPTION
				"Type BITRATE_CONTROL"
			SYNTAX INTEGER
				{
				unknown(-3),
				range-min(0),
				range-max(65535)
				}

		BitrateRead ::= TEXTUAL-CONVENTION
			STATUS current
			DESCRIPTION
				"Type BITRATE_READ"
			SYNTAX INTEGER
				{
				unknown(-3),
				range-min(0),
				range-max(16777215)
				}

		BitsPerSample ::= TEXTUAL-CONVENTION
			STATUS current
			DESCRIPTION
				"Type BITS_PER_SAMPLE"
			SYNTAX INTEGER
				{
				unknown(-3),
				sel16-bits(0),
				sel20-bits(1),
				sel24-bits(2)
				}

		BlackOffset1 ::= TEXTUAL-CONVENTION
			STATUS current
			DESCRIPTION
				"Type BLACK_OFFSET_1"
			SYNTAX INTEGER
				{
				unknown(-3),
				range-min(0),
				range-max(255)
				}

		BlackOffset2 ::= TEXTUAL-CONVENTION
			STATUS current
			DESCRIPTION
				"Type BLACK_OFFSET_2"
			SYNTAX INTEGER
				{
				unknown(-3),
				range-min(0),
				range-max(255)
				}

		BlackThreshold ::= TEXTUAL-CONVENTION
			STATUS current
			DESCRIPTION
				"Type BLACK_THRESHOLD"
			SYNTAX INTEGER
				{
				unknown(-3),
				range-min(0),
				range-max(255)
				}

		BlindModeStat ::= TEXTUAL-CONVENTION
			STATUS current
			DESCRIPTION
				"Type BLIND_MODE_STAT"
			SYNTAX INTEGER
				{
				unknown(-3),
				main(0),
				alternative(1)
				}

		BreakDuration ::= TEXTUAL-CONVENTION
			STATUS current
			DESCRIPTION
				"Type BREAK_DURATION"
			SYNTAX INTEGER
				{
				unknown(-3),
				range-min(0),
				range-max(65535)
				}

		Brightness ::= TEXTUAL-CONVENTION
			STATUS current
			DESCRIPTION
				"Type BRIGHTNESS"
			SYNTAX INTEGER
				{
				unknown(-3),
				range-min(0),
				range-max(3)
				}

		BufferPercentag ::= TEXTUAL-CONVENTION
			STATUS current
			DESCRIPTION
				"Type BUFFER_PERCENTAG"
			SYNTAX INTEGER
				{
				unknown(-3),
				range-min(0),
				range-max(65535)
				}

		CableLengthX2m ::= TEXTUAL-CONVENTION
			STATUS current
			DESCRIPTION
				"Type CABLE_LENGTH_X2M"
			SYNTAX INTEGER
				{
				unknown(-3),
				range-min(0),
				range-max(255)
				}

		CaptChar1 ::= TEXTUAL-CONVENTION
			STATUS current
			DESCRIPTION
				"Type CAPT_CHAR_1"
			SYNTAX INTEGER
				{
				unknown(-3),
				range-min(32),
				range-max(127)
				}

		CaptColour1 ::= TEXTUAL-CONVENTION
			STATUS current
			DESCRIPTION
				"Type CAPT_COLOUR_1"
			SYNTAX INTEGER
				{
				unknown(-3),
				black(0),
				white(1),
				yellow(2),
				cyan(3),
				green(4),
				magenta(5),
				red(6),
				blue(7)
				}

		CaptColour2 ::= TEXTUAL-CONVENTION
			STATUS current
			DESCRIPTION
				"Type CAPT_COLOUR_2"
			SYNTAX INTEGER
				{
				unknown(-3),
				white(0),
				yellow(1),
				cyan(2),
				green(3),
				magenta(4),
				red(5),
				blue(6),
				black(7)
				}

		CaptMode1 ::= TEXTUAL-CONVENTION
			STATUS current
			DESCRIPTION
				"Type CAPT_MODE_1"
			SYNTAX INTEGER
				{
				unknown(-3),
				solid(0),
				semitransparent1(1),
				transparent(3)
				}

		CaptSet1 ::= TEXTUAL-CONVENTION
			STATUS current
			DESCRIPTION
				"Type CAPT_SET_1"
			SYNTAX INTEGER
				{
				unknown(-3),
				no-text(0),
				caption-1(1),
				caption-2(2),
				caption-3(3),
				caption-4(4),
				caption-5(5)
				}

		Cf1 ::= TEXTUAL-CONVENTION
			STATUS current
			DESCRIPTION
				"Type CF_1"
			SYNTAX INTEGER
				{
				unknown(-3),
				sel4-3(0),
				sel16-9(1)
				}

		ChgOverIn2B ::= TEXTUAL-CONVENTION
			STATUS current
			DESCRIPTION
				"Type CHG_OVER_IN_2_B"
			SYNTAX INTEGER
				{
				unknown(-3),
				channel-1(0),
				channel-2(1)
				}

		ChgOverIn2T ::= TEXTUAL-CONVENTION
			STATUS current
			DESCRIPTION
				"Type CHG_OVER_IN_2_T"
			SYNTAX INTEGER
				{
				unknown(-3),
				ts-1(0),
				ts-2(1)
				}

		ChgOverInput1 ::= TEXTUAL-CONVENTION
			STATUS current
			DESCRIPTION
				"Type CHG_OVER_INPUT_1"
			SYNTAX INTEGER
				{
				unknown(-3),
				main(0),
				reserve(1),
				auxiliar(2)
				}

		ChgOverInput2 ::= TEXTUAL-CONVENTION
			STATUS current
			DESCRIPTION
				"Type CHG_OVER_INPUT_2"
			SYNTAX INTEGER
				{
				unknown(-3),
				main(0),
				reserve(1)
				}

		ChgOverInput3 ::= TEXTUAL-CONVENTION
			STATUS current
			DESCRIPTION
				"Type CHG_OVER_INPUT_3"
			SYNTAX INTEGER
				{
				unknown(-3),
				asi-main(0),
				asi-reserve(1),
				ip-main(2),
				ip-reserve(3)
				}

		ChgOverMode1 ::= TEXTUAL-CONVENTION
			STATUS current
			DESCRIPTION
				"Type CHG_OVER_MODE_1"
			SYNTAX INTEGER
				{
				unknown(-3),
				full-auto(0),
				half-auto(1),
				manual(2),
				gpi(3)
				}

		ChgOverMode2 ::= TEXTUAL-CONVENTION
			STATUS current
			DESCRIPTION
				"Type CHG_OVER_MODE_2"
			SYNTAX INTEGER
				{
				unknown(-3),
				full-auto(0),
				half-auto(1),
				manual(2)
				}

		ChgOverMode3 ::= TEXTUAL-CONVENTION
			STATUS current
			DESCRIPTION
				"Type CHG_OVER_MODE_3"
			SYNTAX INTEGER
				{
				unknown(-3),
				half-auto(0),
				full-auto(1),
				manual-inactive(2),
				manual-active(3)
				}

		ChgOverMode4 ::= TEXTUAL-CONVENTION
			STATUS current
			DESCRIPTION
				"Type CHG_OVER_MODE_4"
			SYNTAX INTEGER
				{
				unknown(-3),
				remote(0),
				manual(1)
				}

		ClkStatus ::= TEXTUAL-CONVENTION
			STATUS current
			DESCRIPTION
				"Type CLK_STATUS"
			SYNTAX INTEGER
				{
				unknown(-3),
				unlocked(0),
				locked(1),
				holdove(2),
				relock(3)
				}

		ClockAmPm ::= TEXTUAL-CONVENTION
			STATUS current
			DESCRIPTION
				"Type CLOCK_AM_PM"
			SYNTAX INTEGER
				{
				unknown(-3),
				sel24h(0),
				sel12h(1),
				sel12h-am-pm(3)
				}

		ClockFormat ::= TEXTUAL-CONVENTION
			STATUS current
			DESCRIPTION
				"Type CLOCK_FORMAT"
			SYNTAX INTEGER
				{
				unknown(-3),
				hh-mm-ss-fr-f(0),
				hh-mm-ss-fr(1),
				hh-mm-ss(2),
				hh-mm(3)
				}

		ClockPosition ::= TEXTUAL-CONVENTION
			STATUS current
			DESCRIPTION
				"Type CLOCK_POSITION"
			SYNTAX INTEGER
				{
				unknown(-3),
				top-left(0),
				top-center(1),
				top-right(2),
				mid-left(3),
				mid-center(4),
				mid-right(5),
				bottom-left(6),
				bottom-center(7),
				bottom-right(8)
				}

		ClockSize ::= TEXTUAL-CONVENTION
			STATUS current
			DESCRIPTION
				"Type CLOCK_SIZE"
			SYNTAX INTEGER
				{
				unknown(-3),
				small(0),
				big(1)
				}

		Code4Bit ::= TEXTUAL-CONVENTION
			STATUS current
			DESCRIPTION
				"Type CODE_4_BIT"
			SYNTAX INTEGER
				{
				unknown(-3),
				sel0000(0),
				sel0001(1),
				sel0010(2),
				sel0011(3),
				sel0100(4),
				sel0101(5),
				sel0110(6),
				sel0111(7),
				sel1000(8),
				sel1001(9),
				sel1010(10),
				sel1011(11),
				sel1100(12),
				sel1101(13),
				sel1110(14),
				sel1111(15)
				}

		CodeGen ::= TEXTUAL-CONVENTION
			STATUS current
			DESCRIPTION
				"Type CODE_GEN"
			SYNTAX INTEGER
				{
				unknown(-3),
				pips(0),
				w482(1),
				afnor87500oririg-b(2)
				}

		CrawlSpeed ::= TEXTUAL-CONVENTION
			STATUS current
			DESCRIPTION
				"Type CRAWL_SPEED"
			SYNTAX INTEGER
				{
				unknown(-3),
				range-min(0),
				range-max(15)
				}

		Dad2Level ::= TEXTUAL-CONVENTION
			STATUS current
			DESCRIPTION
				"Type DAD2_LEVEL"
			SYNTAX INTEGER
				{
				unknown(-3),
				range-min(0),
				range-max(255)
				}

		DateFmt ::= TEXTUAL-CONVENTION
			STATUS current
			DESCRIPTION
				"Type DATE_FMT"
			SYNTAX INTEGER
				{
				unknown(-3),
				tve(0),
				bbc(1),
				smpte309(2),
				smpte309mjd(3)
				}

		Day ::= TEXTUAL-CONVENTION
			STATUS current
			DESCRIPTION
				"Type DAY"
			SYNTAX INTEGER
				{
				unknown(-3),
				sunday(0),
				monday(1),
				tuesday(2),
				wednesday(3),
				thursday(4),
				friday(5),
				saturday(6)
				}

		DdbSlots ::= TEXTUAL-CONVENTION
			STATUS current
			DESCRIPTION
				"Type DDB_SLOTS"
			SYNTAX INTEGER
				{
				unknown(-3),
				sel1-2(0),
				sel3-4(1),
				sel5-6(2),
				sel7-8(3),
				none(8)
				}

		DeintAlgorithm ::= TEXTUAL-CONVENTION
			STATUS current
			DESCRIPTION
				"Type DEINT_ALGORITHM"
			SYNTAX INTEGER
				{
				unknown(-3),
				mot-adap(0),
				mot-adapormot-comp(1),
				fld-repl(2),
				edge-lin-avg(4)
				}

		DelayAud ::= TEXTUAL-CONVENTION
			STATUS current
			DESCRIPTION
				"Type DELAY_AUD"
			SYNTAX INTEGER
				{
				unknown(-3),
				range-min(0),
				range-max(16777215)
				}

		DelayFram1 ::= TEXTUAL-CONVENTION
			STATUS current
			DESCRIPTION
				"Type DELAY_FRAM_1"
			SYNTAX INTEGER
				{
				unknown(-3),
				range-min(0),
				range-max(3)
				}

		DelayFram2 ::= TEXTUAL-CONVENTION
			STATUS current
			DESCRIPTION
				"Type DELAY_FRAM_2"
			SYNTAX INTEGER
				{
				unknown(-3),
				range-min(0),
				range-max(255)
				}

		DelayFram3 ::= TEXTUAL-CONVENTION
			STATUS current
			DESCRIPTION
				"Type DELAY_FRAM_3"
			SYNTAX INTEGER
				{
				unknown(-3),
				range-min(0),
				range-max(126)
				}

		DelayFram4 ::= TEXTUAL-CONVENTION
			STATUS current
			DESCRIPTION
				"Type DELAY_FRAM_4"
			SYNTAX INTEGER
				{
				unknown(-3),
				range-min(0),
				range-max(7)
				}

		DelayFram5 ::= TEXTUAL-CONVENTION
			STATUS current
			DESCRIPTION
				"Type DELAY_FRAM_5"
			SYNTAX INTEGER
				{
				unknown(-3),
				range-min(0),
				range-max(15)
				}

		DelayLines1 ::= TEXTUAL-CONVENTION
			STATUS current
			DESCRIPTION
				"Type DELAY_LINES_1"
			SYNTAX INTEGER
				{
				unknown(-3),
				range-min(0),
				range-max(624)
				}

		DelayLines2 ::= TEXTUAL-CONVENTION
			STATUS current
			DESCRIPTION
				"Type DELAY_LINES_2"
			SYNTAX INTEGER
				{
				unknown(-3),
				range-min(0),
				range-max(1124)
				}

		DelayLines3 ::= TEXTUAL-CONVENTION
			STATUS current
			DESCRIPTION
				"Type DELAY_LINES_3"
			SYNTAX INTEGER
				{
				unknown(-3),
				range-min(0),
				range-max(2249)
				}

		DelayPacket1 ::= TEXTUAL-CONVENTION
			STATUS current
			DESCRIPTION
				"Type DELAY_PACKET_1"
			SYNTAX INTEGER
				{
				unknown(-3),
				range-min(0),
				range-max(32767)
				}

		DelayPacket2 ::= TEXTUAL-CONVENTION
			STATUS current
			DESCRIPTION
				"Type DELAY_PACKET_2"
			SYNTAX INTEGER
				{
				unknown(-3),
				range-min(0),
				range-max(65535)
				}

		DelayPixel1 ::= TEXTUAL-CONVENTION
			STATUS current
			DESCRIPTION
				"Type DELAY_PIXEL_1"
			SYNTAX INTEGER
				{
				unknown(-3),
				range-min(0),
				range-max(1727)
				}

		DelayPixel2 ::= TEXTUAL-CONVENTION
			STATUS current
			DESCRIPTION
				"Type DELAY_PIXEL_2"
			SYNTAX INTEGER
				{
				unknown(-3),
				range-min(0),
				range-max(65535)
				}

		DelayPixel3 ::= TEXTUAL-CONVENTION
			STATUS current
			DESCRIPTION
				"Type DELAY_PIXEL_3"
			SYNTAX INTEGER
				{
				unknown(-3),
				range-min(0),
				range-max(863)
				}

		DelayPixel4 ::= TEXTUAL-CONVENTION
			STATUS current
			DESCRIPTION
				"Type DELAY_PIXEL_4"
			SYNTAX INTEGER
				{
				unknown(-3),
				range-min(0),
				range-max(4124)
				}

		DelayPixel5 ::= TEXTUAL-CONVENTION
			STATUS current
			DESCRIPTION
				"Type DELAY_PIXEL_5"
			SYNTAX INTEGER
				{
				unknown(-3),
				range-min(0),
				range-max(2639)
				}

		DelayPixel6 ::= TEXTUAL-CONVENTION
			STATUS current
			DESCRIPTION
				"Type DELAY_PIXEL_6"
			SYNTAX INTEGER
				{
				unknown(-3),
				range-min(0),
				range-max(5279)
				}

		DelayPixelD8 ::= TEXTUAL-CONVENTION
			STATUS current
			DESCRIPTION
				"Type DELAY_PIXEL_D8"
			SYNTAX INTEGER
				{
				unknown(-3),
				range-min(0),
				range-max(7)
				}

		DelaySamp1 ::= TEXTUAL-CONVENTION
			STATUS current
			DESCRIPTION
				"Type DELAY_SAMP_1"
			SYNTAX INTEGER
				{
				unknown(-3),
				range-min(0),
				range-max(65535)
				}

		DelaySamp2 ::= TEXTUAL-CONVENTION
			STATUS current
			DESCRIPTION
				"Type DELAY_SAMP_2"
			SYNTAX INTEGER
				{
				unknown(-3),
				range-min(0),
				range-max(255)
				}

		DelaySamp3 ::= TEXTUAL-CONVENTION
			STATUS current
			DESCRIPTION
				"Type DELAY_SAMP_3"
			SYNTAX INTEGER
				{
				unknown(-3),
				range-min(0),
				range-max(16383)
				}

		DelayX02Ms ::= TEXTUAL-CONVENTION
			STATUS current
			DESCRIPTION
				"Type DELAY_X0_2_MS"
			SYNTAX INTEGER
				{
				unknown(-3),
				range-min(0),
				range-max(65535)
				}

		DelayX1Ms ::= TEXTUAL-CONVENTION
			STATUS current
			DESCRIPTION
				"Type DELAY_X1_MS"
			SYNTAX INTEGER
				{
				unknown(-3),
				range-min(0),
				range-max(65535)
				}

		DelayX1Ns ::= TEXTUAL-CONVENTION
			STATUS current
			DESCRIPTION
				"Type DELAY_X1_NS"
			SYNTAX INTEGER
				{
				unknown(-3),
				range-min(0),
				range-max(65535)
				}

		DelayX1S ::= TEXTUAL-CONVENTION
			STATUS current
			DESCRIPTION
				"Type DELAY_X1_S"
			SYNTAX INTEGER
				{
				unknown(-3),
				range-min(0),
				range-max(255)
				}

		DelayX1S127 ::= TEXTUAL-CONVENTION
			STATUS current
			DESCRIPTION
				"Type DELAY_X1_S_127"
			SYNTAX INTEGER
				{
				unknown(-3),
				range-min(0),
				range-max(127)
				}

		DelayX1004bNs ::= TEXTUAL-CONVENTION
			STATUS current
			DESCRIPTION
				"Type DELAY_X100_4B_NS"
			SYNTAX INTEGER
				{
				unknown(-3),
				range-min(0),
				range-max(2147483647)
				}

		DelayX100Ns ::= TEXTUAL-CONVENTION
			STATUS current
			DESCRIPTION
				"Type DELAY_X100_NS"
			SYNTAX INTEGER
				{
				unknown(-3),
				range-min(0),
				range-max(9999999)
				}

		DelayX131Ms ::= TEXTUAL-CONVENTION
			STATUS current
			DESCRIPTION
				"Type DELAY_X13_1_MS"
			SYNTAX INTEGER
				{
				unknown(-3),
				range-min(0),
				range-max(255)
				}

		DelayX144Ps ::= TEXTUAL-CONVENTION
			STATUS current
			DESCRIPTION
				"Type DELAY_X144_PS"
			SYNTAX INTEGER
				{
				unknown(-3),
				range-min(0),
				range-max(255)
				}

		DelayX18Ns ::= TEXTUAL-CONVENTION
			STATUS current
			DESCRIPTION
				"Type DELAY_X18_NS"
			SYNTAX INTEGER
				{
				unknown(-3),
				range-min(0),
				range-max(268435455)
				}

		DelayX2Ns ::= TEXTUAL-CONVENTION
			STATUS current
			DESCRIPTION
				"Type DELAY_X2_NS"
			SYNTAX INTEGER
				{
				unknown(-3),
				range-min(0),
				range-max(255)
				}

		DelayX20Us ::= TEXTUAL-CONVENTION
			STATUS current
			DESCRIPTION
				"Type DELAY_X20_US"
			SYNTAX INTEGER
				{
				unknown(-3),
				range-min(0),
				range-max(2047)
				}

		DelayX256Sampl ::= TEXTUAL-CONVENTION
			STATUS current
			DESCRIPTION
				"Type DELAY_X256_SAMPL"
			SYNTAX INTEGER
				{
				unknown(-3),
				range-min(0),
				range-max(255)
				}

		DelayX65Ms ::= TEXTUAL-CONVENTION
			STATUS current
			DESCRIPTION
				"Type DELAY_X6_5_MS"
			SYNTAX INTEGER
				{
				unknown(-3),
				range-min(0),
				range-max(255)
				}

		DelayX74Ns ::= TEXTUAL-CONVENTION
			STATUS current
			DESCRIPTION
				"Type DELAY_X7_4_NS"
			SYNTAX INTEGER
				{
				unknown(-3),
				range-min(0),
				range-max(2147483647)
				}

		DetBb525 ::= TEXTUAL-CONVENTION
			STATUS current
			DESCRIPTION
				"Type DET_BB_525"
			SYNTAX INTEGER
				{
				unknown(-3),
				no-0(0),
				yes(1),
				no-2(2),
				no-3(3)
				}

		DetBb625 ::= TEXTUAL-CONVENTION
			STATUS current
			DESCRIPTION
				"Type DET_BB_625"
			SYNTAX INTEGER
				{
				unknown(-3),
				no-0(0),
				no-1(1),
				yes(2),
				no-3(3)
				}

		DtmfCode ::= TEXTUAL-CONVENTION
			STATUS current
			DESCRIPTION
				"Type DTMF_CODE"
			SYNTAX INTEGER
				{
				unknown(-3),
				range-min(0),
				range-max(15)
				}

		DvbTModeIsw ::= TEXTUAL-CONVENTION
			STATUS current
			DESCRIPTION
				"Type DVB_T_MODE_ISW"
			SYNTAX INTEGER
				{
				unknown(-3),
				generic-dvb(0),
				dvb-t(1),
				dvb-t2(2)
				}

		DvbT2Locked ::= TEXTUAL-CONVENTION
			STATUS current
			DESCRIPTION
				"Type DVB_T2_LOCKED"
			SYNTAX INTEGER
				{
				unknown(-3),
				unlocked(0),
				locked-null-ts(1),
				locked-relative-ts(2),
				locked-absolute-ts(3)
				}

		DvbT2SyncMode ::= TEXTUAL-CONVENTION
			STATUS current
			DESCRIPTION
				"Type DVB_T2_SYNC_MODE"
			SYNTAX INTEGER
				{
				unknown(-3),
				auto(0),
				manual-pid(1)
				}

		EmbedGroup ::= TEXTUAL-CONVENTION
			STATUS current
			DESCRIPTION
				"Type EMBED_GROUP"
			SYNTAX INTEGER
				{
				unknown(-3),
				group1(0),
				group2(1),
				group3(2),
				group4(3)
				}

		EopInput ::= TEXTUAL-CONVENTION
			STATUS current
			DESCRIPTION
				"Type EOP_INPUT"
			SYNTAX INTEGER
				{
				unknown(-3),
				sfp(0),
				bnc(1),
				other-sect(2),
				backplane(3)
				}

		EqualLength ::= TEXTUAL-CONVENTION
			STATUS current
			DESCRIPTION
				"Type EQUAL_LENGTH"
			SYNTAX INTEGER
				{
				unknown(-3),
				range-min(0),
				range-max(15)
				}

		EthMode ::= TEXTUAL-CONVENTION
			STATUS current
			DESCRIPTION
				"Type ETH_MODE"
			SYNTAX INTEGER
				{
				unknown(-3),
				auto(0),
				sel10mbps-hd(2),
				sel10mbps-fd(3),
				sel100mbps-hd(4),
				sel100mbps-fd(5),
				sel1gbps-fd(7)
				}

		EthMode2000 ::= TEXTUAL-CONVENTION
			STATUS current
			DESCRIPTION
				"Type ETH_MODE_2000"
			SYNTAX INTEGER
				{
				unknown(-3),
				range-min(0),
				range-max(7)
				}

		EthMode2g5 ::= TEXTUAL-CONVENTION
			STATUS current
			DESCRIPTION
				"Type ETH_MODE_2G5"
			SYNTAX INTEGER
				{
				unknown(-3),
				sel2dot5gbps(1),
				sel1gbps(0)
				}

		EthStatus ::= TEXTUAL-CONVENTION
			STATUS current
			DESCRIPTION
				"Type ETH_STATUS"
			SYNTAX INTEGER
				{
				unknown(-3),
				down(0),
				up(1)
				}

		FecMode ::= TEXTUAL-CONVENTION
			STATUS current
			DESCRIPTION
				"Type FEC_MODE"
			SYNTAX INTEGER
				{
				unknown(-3),
				udp(0),
				rtp-no-fec(1),
				rtp-fec-a(2),
				rtp-fec-b(3)
				}

		FecModeSte ::= TEXTUAL-CONVENTION
			STATUS current
			DESCRIPTION
				"Type FEC_MODE_STE"
			SYNTAX INTEGER
				{
				unknown(-3),
				rtp-no-fec(0),
				rtp-fec-a(1),
				rtp-fec-b(2)
				}

		Frame ::= TEXTUAL-CONVENTION
			STATUS current
			DESCRIPTION
				"Type FRAME"
			SYNTAX INTEGER
				{
				unknown(-3),
				range-min(0),
				range-max(24)
				}

		FreqRange ::= TEXTUAL-CONVENTION
			STATUS current
			DESCRIPTION
				"Type FREQ_RANGE"
			SYNTAX INTEGER
				{
				unknown(-3),
				hz(0),
				khz(1)
				}

		FrqDrft3 ::= TEXTUAL-CONVENTION
			STATUS current
			DESCRIPTION
				"Type FRQ_DRFT_3"
			SYNTAX INTEGER
				{
				unknown(-3),
				range-min(0),
				range-max(2147483647)
				}

		FrqGen ::= TEXTUAL-CONVENTION
			STATUS current
			DESCRIPTION
				"Type FRQ_GEN"
			SYNTAX INTEGER
				{
				unknown(-3),
				range-min(0),
				range-max(255)
				}

		Gain24dbMute ::= TEXTUAL-CONVENTION
			STATUS current
			DESCRIPTION
				"Type GAIN_24DB_MUTE"
			SYNTAX INTEGER
				{
				unknown(-3),
				range-min(0),
				range-max(127)
				}

		Gain315dbMute ::= TEXTUAL-CONVENTION
			STATUS current
			DESCRIPTION
				"Type GAIN_31_5DB_MUTE"
			SYNTAX INTEGER
				{
				unknown(-3),
				range-min(0),
				range-max(255)
				}

		GainDb1 ::= TEXTUAL-CONVENTION
			STATUS current
			DESCRIPTION
				"Type GAIN_DB_1"
			SYNTAX INTEGER
				{
				unknown(-3),
				range-min(0),
				range-max(255)
				}

		GainDb2 ::= TEXTUAL-CONVENTION
			STATUS current
			DESCRIPTION
				"Type GAIN_DB_2"
			SYNTAX INTEGER
				{
				unknown(-3),
				range-min(0),
				range-max(255)
				}

		GainLin1 ::= TEXTUAL-CONVENTION
			STATUS current
			DESCRIPTION
				"Type GAIN_LIN_1"
			SYNTAX INTEGER
				{
				unknown(-3),
				range-min(0),
				range-max(255)
				}

		GatewayInput3 ::= TEXTUAL-CONVENTION
			STATUS current
			DESCRIPTION
				"Type GATEWAY_INPUT_3"
			SYNTAX INTEGER
				{
				unknown(-3),
				asi-in-1(0),
				asi-in-2(1),
				ip-in-1(2),
				ip-in-2(3)
				}

		GenlockM0de2 ::= TEXTUAL-CONVENTION
			STATUS current
			DESCRIPTION
				"Type GENLOCK_M0DE_2"
			SYNTAX INTEGER
				{
				unknown(-3),
				analog-video(0),
				digital-video(1)
				}

		GenlockMode1 ::= TEXTUAL-CONVENTION
			STATUS current
			DESCRIPTION
				"Type GENLOCK_MODE_1"
			SYNTAX INTEGER
				{
				unknown(-3),
				analog-video(0),
				digital-video(1),
				chassis-int-ref(2)
				}

		GpdCurrent ::= TEXTUAL-CONVENTION
			STATUS current
			DESCRIPTION
				"Type GPD_CURRENT"
			SYNTAX INTEGER
				{
				unknown(-3),
				range-min(0),
				range-max(255)
				}

		GpdVoltage ::= TEXTUAL-CONVENTION
			STATUS current
			DESCRIPTION
				"Type GPD_VOLTAGE"
			SYNTAX INTEGER
				{
				unknown(-3),
				range-min(0),
				range-max(255)
				}

		GpiMode ::= TEXTUAL-CONVENTION
			STATUS current
			DESCRIPTION
				"Type GPI_MODE"
			SYNTAX INTEGER
				{
				unknown(-3),
				act-closed-lev(0),
				act-open-level(1),
				act-clos-edge(2),
				act-op-edge(3)
				}

		GpioMode ::= TEXTUAL-CONVENTION
			STATUS current
			DESCRIPTION
				"Type GPIO_MODE"
			SYNTAX INTEGER
				{
				unknown(-3),
				gpi-mode(0),
				gpo-mode(1),
				preset-mode(2),
				tx-ip-redundant-mode(3)
				}

		GpioModeB ::= TEXTUAL-CONVENTION
			STATUS current
			DESCRIPTION
				"Type GPIO_MODE_B"
			SYNTAX INTEGER
				{
				unknown(-3),
				gpio-mode(0),
				preset-mode(1)
				}

		Gpos010 ::= TEXTUAL-CONVENTION
			STATUS current
			DESCRIPTION
				"Type GPOS_0_10"
			SYNTAX INTEGER
				{
				unknown(-3),
				range-min(0),
				range-max(10)
				}

		Gpos0255 ::= TEXTUAL-CONVENTION
			STATUS current
			DESCRIPTION
				"Type GPOS_0_255"
			SYNTAX INTEGER
				{
				unknown(-3),
				range-min(0),
				range-max(255)
				}

		GpsAdqStat1 ::= TEXTUAL-CONVENTION
			STATUS current
			DESCRIPTION
				"Type GPS_ADQ_STAT_1"
			SYNTAX INTEGER
				{
				unknown(-3),
				no-signal-0(0),
				no-signal-1(1),
				no-signal-2(2),
				synchro-3(3),
				synchro-4(4),
				synchro-5(5),
				synchro-6(6),
				holdover-7(7),
				holdover-8(8)
				}

		GpsAdqStat2 ::= TEXTUAL-CONVENTION
			STATUS current
			DESCRIPTION
				"Type GPS_ADQ_STAT_2"
			SYNTAX INTEGER
				{
				unknown(-3),
				acq-0(0),
				acq-1(1),
				acq-2(2),
				acq-3(3),
				acq-4(4),
				track-5(5),
				phs-rst-6(6),
				holdover-7(7),
				holdover-8(8),
				drift-9(9),
				dds-rmt-10(10)
				}

		GpsAntenaStat ::= TEXTUAL-CONVENTION
			STATUS current
			DESCRIPTION
				"Type GPS_ANTENA_STAT"
			SYNTAX INTEGER
				{
				unknown(-3),
				ok(0),
				overcurrent(1),
				no-present(2)
				}

		GpsFrqDrftEst ::= TEXTUAL-CONVENTION
			STATUS current
			DESCRIPTION
				"Type GPS_FRQ_DRFT_EST"
			SYNTAX INTEGER
				{
				unknown(-3),
				range-min(0),
				range-max(255)
				}

		GpsHoldovrTime ::= TEXTUAL-CONVENTION
			STATUS current
			DESCRIPTION
				"Type GPS_HOLDOVR_TIME"
			SYNTAX INTEGER
				{
				unknown(-3),
				range-min(0),
				range-max(65535)
				}

		GpsPhsDrftEst ::= TEXTUAL-CONVENTION
			STATUS current
			DESCRIPTION
				"Type GPS_PHS_DRFT_EST"
			SYNTAX INTEGER
				{
				unknown(-3),
				range-min(0),
				range-max(255)
				}

		GpsSatRxStat ::= TEXTUAL-CONVENTION
			STATUS current
			DESCRIPTION
				"Type GPS_SAT_RX_STAT"
			SYNTAX INTEGER
				{
				unknown(-3),
				unknown-0(0),
				unknown-1(1),
				bad-geometry-2(2),
				adquiring-3(3),
				position-hold-4(4),
				unknown-5(5),
				sel2d-fix-6(6),
				sel3d-fix-7(7)
				}

		GpsSatellites ::= TEXTUAL-CONVENTION
			STATUS current
			DESCRIPTION
				"Type GPS_SATELLITES"
			SYNTAX INTEGER
				{
				unknown(-3),
				range-min(0),
				range-max(15)
				}

		Gps2FixMode ::= TEXTUAL-CONVENTION
			STATUS current
			DESCRIPTION
				"Type GPS2_FIX_MODE"
			SYNTAX INTEGER
				{
				unknown(-3),
				range-min(0),
				range-max(7)
				}

		Gps2FrqTemDrf ::= TEXTUAL-CONVENTION
			STATUS current
			DESCRIPTION
				"Type GPS2_FRQ_TEM_DRF"
			SYNTAX INTEGER
				{
				unknown(-3),
				range-min(0),
				range-max(65535)
				}

		Gps2FrqTimDrf ::= TEXTUAL-CONVENTION
			STATUS current
			DESCRIPTION
				"Type GPS2_FRQ_TIM_DRF"
			SYNTAX INTEGER
				{
				unknown(-3),
				range-min(0),
				range-max(65535)
				}

		Gps2SyncMode ::= TEXTUAL-CONVENTION
			STATUS current
			DESCRIPTION
				"Type GPS2_SYNC_MODE"
			SYNTAX INTEGER
				{
				unknown(-3),
				gnss(0),
				ptp(1),
				gnss-ptp(2),
				holdover(3)
				}

		Gps2SyncState ::= TEXTUAL-CONVENTION
			STATUS current
			DESCRIPTION
				"Type GPS2_SYNC_STATE"
			SYNTAX INTEGER
				{
				unknown(-3),
				cold-start(0),
				holdover-uncal(1),
				holdover(2),
				unlock-gnss(3),
				locked-gnss(4),
				relock-gnss(5),
				unlock-ptp(6),
				locked-ptp(7),
				relock-ptp(8)
				}

		GrpMxInput1 ::= TEXTUAL-CONVENTION
			STATUS current
			DESCRIPTION
				"Type GRP_MX_INPUT_1"
			SYNTAX INTEGER
				{
				unknown(-3),
				ch1(0),
				ch2(1),
				ch3(2),
				ch4(3)
				}

		HaeSampClk ::= TEXTUAL-CONVENTION
			STATUS current
			DESCRIPTION
				"Type HAE_SAMP_CLK"
			SYNTAX INTEGER
				{
				unknown(-3),
				section-b(0),
				section-a(1)
				}

		Hde2AesSrc ::= TEXTUAL-CONVENTION
			STATUS current
			DESCRIPTION
				"Type HDE2_AES_SRC"
			SYNTAX INTEGER
				{
				unknown(-3),
				range-min(0),
				range-max(32)
				}

		Hde2L2rSrc ::= TEXTUAL-CONVENTION
			STATUS current
			DESCRIPTION
				"Type HDE2_L2R_SRC"
			SYNTAX INTEGER
				{
				unknown(-3),
				aes1-l(0),
				aes1-r(1),
				aes-2(2),
				aes2-r(3),
				aes3-l(4),
				aes3-r(5),
				aes4-l(6),
				aes4-r(7),
				aes5-l(8),
				aes5-r(9),
				aes6-l(10),
				aes6-r(11),
				aes7-l(12),
				aes7-r(13),
				aes8-l(14),
				aes8-r(15),
				l2r-in(16)
				}

		Hde2L2rSrcA ::= TEXTUAL-CONVENTION
			STATUS current
			DESCRIPTION
				"Type HDE2_L2R_SRC_A"
			SYNTAX INTEGER
				{
				unknown(-3),
				range-min(0),
				range-max(16)
				}

		Hde2R2lSrc ::= TEXTUAL-CONVENTION
			STATUS current
			DESCRIPTION
				"Type HDE2_R2L_SRC"
			SYNTAX INTEGER
				{
				unknown(-3),
				aes1-l(0),
				aes1-r(1),
				aes-2(2),
				aes2-r(3),
				aes3-l(4),
				aes3-r(5),
				aes4-l(6),
				aes4-r(7),
				aes5-l(8),
				aes5-r(9),
				aes6-l(10),
				aes6-r(11),
				aes7-l(12),
				aes7-r(13),
				aes8-l(14),
				aes8-r(15),
				r2l-in(16)
				}

		Hde2R2lSrcA ::= TEXTUAL-CONVENTION
			STATUS current
			DESCRIPTION
				"Type HDE2_R2L_SRC_A"
			SYNTAX INTEGER
				{
				unknown(-3),
				range-min(0),
				range-max(16)
				}

		HliLdStat ::= TEXTUAL-CONVENTION
			STATUS current
			DESCRIPTION
				"Type HLI_LD_STAT"
			SYNTAX INTEGER
				{
				unknown(-3),
				range-min(0),
				range-max(255)
				}

		Hli2AnimType ::= TEXTUAL-CONVENTION
			STATUS current
			DESCRIPTION
				"Type HLI2_ANIM_TYPE"
			SYNTAX INTEGER
				{
				unknown(-3),
				start-end(0),
				start-pause-cont-end(1),
				loop(2),
				start-pause-reverse-end(3)
				}

		Hli2LayerType ::= TEXTUAL-CONVENTION
			STATUS current
			DESCRIPTION
				"Type HLI2_LAYER_TYPE"
			SYNTAX INTEGER
				{
				unknown(-3),
				static-logos(0),
				animated-logos(1),
				teletext(2),
				captions(3)
				}

		Hli2MixType ::= TEXTUAL-CONVENTION
			STATUS current
			DESCRIPTION
				"Type HLI2_MIX_TYPE"
			SYNTAX INTEGER
				{
				unknown(-3),
				fade-out-fade-in(0),
				sum(1)
				}

		HopGpoSrcSel ::= TEXTUAL-CONVENTION
			STATUS current
			DESCRIPTION
				"Type HOP_GPO_SRC_SEL"
			SYNTAX INTEGER
				{
				unknown(-3),
				txt(0),
				audio(1),
				scte-104(2)
				}

		HswFreezeMode ::= TEXTUAL-CONVENTION
			STATUS current
			DESCRIPTION
				"Type HSW_FREEZE_MODE"
			SYNTAX INTEGER
				{
				unknown(-3),
				active-video(0),
				full-frame(1)
				}

		HswGpoState ::= TEXTUAL-CONVENTION
			STATUS current
			DESCRIPTION
				"Type HSW_GPO_STATE"
			SYNTAX INTEGER
				{
				unknown(-3),
				open-open(0),
				open-closed(1),
				closed-open(2),
				closed-closed(3)
				}

		HswMapState ::= TEXTUAL-CONVENTION
			STATUS current
			DESCRIPTION
				"Type HSW_MAP_STATE"
			SYNTAX INTEGER
				{
				unknown(-3),
				straight(0),
				crossed(1),
				both-in1(2),
				both-in2(3)
				}

		HswOperMode ::= TEXTUAL-CONVENTION
			STATUS current
			DESCRIPTION
				"Type HSW_OPER_MODE"
			SYNTAX INTEGER
				{
				unknown(-3),
				changeover(0),
				sync-chgover(1)
				}

		HswOutput ::= TEXTUAL-CONVENTION
			STATUS current
			DESCRIPTION
				"Type HSW_OUTPUT"
			SYNTAX INTEGER
				{
				unknown(-3),
				input-1(0),
				input-2(1),
				black(2),
				mute(3)
				}

		HswState ::= TEXTUAL-CONVENTION
			STATUS current
			DESCRIPTION
				"Type HSW_STATE"
			SYNTAX INTEGER
				{
				unknown(-3),
				state-a(0),
				state-b(1)
				}

		HswSwMode ::= TEXTUAL-CONVENTION
			STATUS current
			DESCRIPTION
				"Type HSW_SW_MODE"
			SYNTAX INTEGER
				{
				unknown(-3),
				full-auto(0),
				half-auto(1),
				blind-half-auto(2),
				manual(3),
				gpi(4)
				}

		HswTiming ::= TEXTUAL-CONVENTION
			STATUS current
			DESCRIPTION
				"Type HSW_TIMING"
			SYNTAX INTEGER
				{
				unknown(-3),
				timing-1(0),
				timing-2(1)
				}

		Hsw2SwMode ::= TEXTUAL-CONVENTION
			STATUS current
			DESCRIPTION
				"Type HSW2_SW_MODE"
			SYNTAX INTEGER
				{
				unknown(-3),
				full-auto(0),
				half-auto(1),
				manual(3)
				}

		Hsw3SwMode ::= TEXTUAL-CONVENTION
			STATUS current
			DESCRIPTION
				"Type HSW3_SW_MODE"
			SYNTAX INTEGER
				{
				unknown(-3),
				full-auto(0),
				half-auto(1),
				manual(2)
				}

		HvpLockStatus ::= TEXTUAL-CONVENTION
			STATUS current
			DESCRIPTION
				"Type HVP_LOCK_STATUS"
			SYNTAX INTEGER
				{
				unknown(-3),
				unlocked(0),
				locked-sd(1),
				locked-hd(2),
				locked-3g(3)
				}

		HvpMode ::= TEXTUAL-CONVENTION
			STATUS current
			DESCRIPTION
				"Type HVP_MODE"
			SYNTAX INTEGER
				{
				unknown(-3),
				sel12x2(0),
				sel10x4(1),
				sel6x2-loop(2),
				sel6x4-loop(3)
				}

		Hvp2Input ::= TEXTUAL-CONVENTION
			STATUS current
			DESCRIPTION
				"Type HVP2_INPUT"
			SYNTAX INTEGER
				{
				unknown(-3),
				bnc(0),
				backplane-0(1),
				backplane-1(2),
				none(3)
				}

		Impedance ::= TEXTUAL-CONVENTION
			STATUS current
			DESCRIPTION
				"Type IMPEDANCE"
			SYNTAX INTEGER
				{
				unknown(-3),
				sel50-ohms(0),
				sel75-ohms(1)
				}

		Incompatibility ::= TEXTUAL-CONVENTION
			STATUS current
			DESCRIPTION
				"Type INCOMPATIBILITY"
			SYNTAX INTEGER
				{
				unknown(-3),
				compatible(0),
				incompatible(1)
				}

		InputOutput ::= TEXTUAL-CONVENTION
			STATUS current
			DESCRIPTION
				"Type INPUT_OUTPUT"
			SYNTAX INTEGER
				{
				unknown(-3),
				input(0),
				output-prefered-ch(2),
				output-secondary-ch(3)
				}

		InputOutputAux ::= TEXTUAL-CONVENTION
			STATUS current
			DESCRIPTION
				"Type INPUT_OUTPUT_AUX"
			SYNTAX INTEGER
				{
				unknown(-3),
				disabled(0),
				output-prefered-ch(2),
				output-secondary-ch(3)
				}

		Inputs012 ::= TEXTUAL-CONVENTION
			STATUS current
			DESCRIPTION
				"Type INPUTS_0_12"
			SYNTAX INTEGER
				{
				unknown(-3),
				range-min(0),
				range-max(12)
				}

		Inputs06 ::= TEXTUAL-CONVENTION
			STATUS current
			DESCRIPTION
				"Type INPUTS_0_6"
			SYNTAX INTEGER
				{
				unknown(-3),
				range-min(0),
				range-max(6)
				}

		Inputs132 ::= TEXTUAL-CONVENTION
			STATUS current
			DESCRIPTION
				"Type INPUTS_1_32"
			SYNTAX INTEGER
				{
				unknown(-3),
				range-min(1),
				range-max(32)
				}

		InsercionMpx ::= TEXTUAL-CONVENTION
			STATUS current
			DESCRIPTION
				"Type INSERCION_MPX"
			SYNTAX INTEGER
				{
				unknown(-3),
				range-min(0),
				range-max(15)
				}

		Int16 ::= TEXTUAL-CONVENTION
			STATUS current
			DESCRIPTION
				"Type INT_16"
			SYNTAX INTEGER
				{
				unknown(-3),
				range-min(0),
				range-max(65535)
				}

		Int8 ::= TEXTUAL-CONVENTION
			STATUS current
			DESCRIPTION
				"Type INT_8"
			SYNTAX INTEGER
				{
				unknown(-3),
				range-min(0),
				range-max(255)
				}

		IoAesMode ::= TEXTUAL-CONVENTION
			STATUS current
			DESCRIPTION
				"Type IO_AES_MODE"
			SYNTAX INTEGER
				{
				unknown(-3),
				sel8-in(0),
				sel4-inor4-out(1),
				sel4-outor4-in(2),
				sel8-out(3)
				}

		IoAesModeRef ::= TEXTUAL-CONVENTION
			STATUS current
			DESCRIPTION
				"Type IO_AES_MODE_REF"
			SYNTAX INTEGER
				{
				unknown(-3),
				sel8-inputs(0),
				sel4-outputsor4-refdot-inputs(2),
				sel8-outputs(3)
				}

		IoMode ::= TEXTUAL-CONVENTION
			STATUS current
			DESCRIPTION
				"Type IO_MODE"
			SYNTAX INTEGER
				{
				unknown(-3),
				embedder(0),
				deembedder(1)
				}

		IpInterface ::= TEXTUAL-CONVENTION
			STATUS current
			DESCRIPTION
				"Type IP_INTERFACE"
			SYNTAX INTEGER
				{
				unknown(-3),
				range-min(0),
				range-max(1)
				}

		Ipa2EtherStat ::= TEXTUAL-CONVENTION
			STATUS current
			DESCRIPTION
				"Type IPA_2_ETHER_STAT"
			SYNTAX INTEGER
				{
				unknown(-3),
				range-min(0),
				range-max(11)
				}

		Ipa2EtherSys ::= TEXTUAL-CONVENTION
			STATUS current
			DESCRIPTION
				"Type IPA_2_ETHER_SYS"
			SYNTAX INTEGER
				{
				unknown(-3),
				range-min(0),
				range-max(3)
				}

		IpaChSelection ::= TEXTUAL-CONVENTION
			STATUS current
			DESCRIPTION
				"Type IPA_CH_SELECTION"
			SYNTAX INTEGER
				{
				unknown(-3),
				range-min(0),
				range-max(5)
				}

		IpaEtherStat ::= TEXTUAL-CONVENTION
			STATUS current
			DESCRIPTION
				"Type IPA_ETHER_STAT"
			SYNTAX INTEGER
				{
				unknown(-3),
				sel10mbps(5),
				sel100mbps(9),
				sel1gbps(17),
				no-link(0)
				}

		IpaEtherSys ::= TEXTUAL-CONVENTION
			STATUS current
			DESCRIPTION
				"Type IPA_ETHER_SYS"
			SYNTAX INTEGER
				{
				unknown(-3),
				full-duplex(33),
				half-duplex(1),
				no-link(0)
				}

		IpaOutSel ::= TEXTUAL-CONVENTION
			STATUS current
			DESCRIPTION
				"Type IPA_OUT_SEL"
			SYNTAX INTEGER
				{
				unknown(-3),
				selected-channel(0),
				secondary-channel(1)
				}

		IpaPingStat ::= TEXTUAL-CONVENTION
			STATUS current
			DESCRIPTION
				"Type IPA_PING_STAT"
			SYNTAX INTEGER
				{
				unknown(-3),
				dis0(0),
				dis1(1),
				no-resp(2),
				resp-ok(3)
				}

		IpaPrecedence ::= TEXTUAL-CONVENTION
			STATUS current
			DESCRIPTION
				"Type IPA_PRECEDENCE"
			SYNTAX INTEGER
				{
				unknown(-3),
				routine(0),
				priority(1),
				inmediate(2),
				flash(3),
				flash-override(4),
				critic-ecp(5),
				internetwork-control(6),
				network-control(7)
				}

		IpaTxMode ::= TEXTUAL-CONVENTION
			STATUS current
			DESCRIPTION
				"Type IPA_TX_MODE"
			SYNTAX INTEGER
				{
				unknown(-3),
				unicast(0),
				multicast(1)
				}

		IswChSelection ::= TEXTUAL-CONVENTION
			STATUS current
			DESCRIPTION
				"Type ISW_CH_SELECTION"
			SYNTAX INTEGER
				{
				unknown(-3),
				range-min(0),
				range-max(3)
				}

		LedMode ::= TEXTUAL-CONVENTION
			STATUS current
			DESCRIPTION
				"Type LED_MODE"
			SYNTAX INTEGER
				{
				unknown(-3),
				status(0),
				peak-level(1),
				vu-level(2)
				}

		LevelDbHz ::= TEXTUAL-CONVENTION
			STATUS current
			DESCRIPTION
				"Type LEVEL_DB_HZ"
			SYNTAX INTEGER
				{
				unknown(-3),
				range-min(0),
				range-max(255)
				}

		LevelDbX6 ::= TEXTUAL-CONVENTION
			STATUS current
			DESCRIPTION
				"Type LEVEL_DB_X6"
			SYNTAX INTEGER
				{
				unknown(-3),
				range-min(0),
				range-max(3)
				}

		LevelDbfs1 ::= TEXTUAL-CONVENTION
			STATUS current
			DESCRIPTION
				"Type LEVEL_DBFS_1"
			SYNTAX INTEGER
				{
				unknown(-3),
				range-min(0),
				range-max(160)
				}

		LevelDbfs2 ::= TEXTUAL-CONVENTION
			STATUS current
			DESCRIPTION
				"Type LEVEL_DBFS_2"
			SYNTAX INTEGER
				{
				unknown(-3),
				range-min(0),
				range-max(63)
				}

		LevelDbfs2x ::= TEXTUAL-CONVENTION
			STATUS current
			DESCRIPTION
				"Type LEVEL_DBFS_2X"
			SYNTAX INTEGER
				{
				unknown(-3),
				range-min(0),
				range-max(127)
				}

		LevelDbfs3 ::= TEXTUAL-CONVENTION
			STATUS current
			DESCRIPTION
				"Type LEVEL_DBFS_3"
			SYNTAX INTEGER
				{
				unknown(-3),
				range-min(0),
				range-max(160)
				}

		LevelDbfs4 ::= TEXTUAL-CONVENTION
			STATUS current
			DESCRIPTION
				"Type LEVEL_DBFS_4"
			SYNTAX INTEGER
				{
				unknown(-3),
				range-min(1),
				range-max(160)
				}

		LevelDbfs8 ::= TEXTUAL-CONVENTION
			STATUS current
			DESCRIPTION
				"Type LEVEL_DBFS_8"
			SYNTAX INTEGER
				{
				unknown(-3),
				range-min(0),
				range-max(15)
				}

		LevelDbfsA ::= TEXTUAL-CONVENTION
			STATUS current
			DESCRIPTION
				"Type LEVEL_DBFS_A"
			SYNTAX INTEGER
				{
				unknown(-3),
				range-min(0),
				range-max(255)
				}

		LevelDbfsD ::= TEXTUAL-CONVENTION
			STATUS current
			DESCRIPTION
				"Type LEVEL_DBFS_D"
			SYNTAX INTEGER
				{
				unknown(-3),
				range-min(0),
				range-max(63)
				}

		LevelDbfsF ::= TEXTUAL-CONVENTION
			STATUS current
			DESCRIPTION
				"Type LEVEL_DBFS_F"
			SYNTAX INTEGER
				{
				unknown(-3),
				range-min(0),
				range-max(127)
				}

		LevelDbu ::= TEXTUAL-CONVENTION
			STATUS current
			DESCRIPTION
				"Type LEVEL_DBU"
			SYNTAX INTEGER
				{
				unknown(-3),
				range-min(14),
				range-max(24)
				}

		LevelDbu1 ::= TEXTUAL-CONVENTION
			STATUS current
			DESCRIPTION
				"Type LEVEL_DBU_1"
			SYNTAX INTEGER
				{
				unknown(-3),
				range-min(0),
				range-max(255)
				}

		LevelDbuD2 ::= TEXTUAL-CONVENTION
			STATUS current
			DESCRIPTION
				"Type LEVEL_DBU_D2"
			SYNTAX INTEGER
				{
				unknown(-3),
				range-min(0),
				range-max(255)
				}

		LevelDbuD5 ::= TEXTUAL-CONVENTION
			STATUS current
			DESCRIPTION
				"Type LEVEL_DBU_D5"
			SYNTAX INTEGER
				{
				unknown(-3),
				range-min(0),
				range-max(255)
				}

		LevelLkfs2 ::= TEXTUAL-CONVENTION
			STATUS current
			DESCRIPTION
				"Type LEVEL_LKFS_2"
			SYNTAX INTEGER
				{
				unknown(-3),
				range-min(0),
				range-max(31)
				}

		LevelVu2 ::= TEXTUAL-CONVENTION
			STATUS current
			DESCRIPTION
				"Type LEVEL_VU2"
			SYNTAX INTEGER
				{
				unknown(-3),
				range-min(0),
				range-max(255)
				}

		LogoPosH1 ::= TEXTUAL-CONVENTION
			STATUS current
			DESCRIPTION
				"Type LOGO_POS_H_1"
			SYNTAX INTEGER
				{
				unknown(-3),
				range-min(0),
				range-max(359)
				}

		LogoPosV1 ::= TEXTUAL-CONVENTION
			STATUS current
			DESCRIPTION
				"Type LOGO_POS_V_1"
			SYNTAX INTEGER
				{
				unknown(-3),
				range-min(0),
				range-max(312)
				}

		LogoSizH1 ::= TEXTUAL-CONVENTION
			STATUS current
			DESCRIPTION
				"Type LOGO_SIZ_H_1"
			SYNTAX INTEGER
				{
				unknown(-3),
				range-min(0),
				range-max(359)
				}

		LogoSizV1 ::= TEXTUAL-CONVENTION
			STATUS current
			DESCRIPTION
				"Type LOGO_SIZ_V_1"
			SYNTAX INTEGER
				{
				unknown(-3),
				range-min(0),
				range-max(624)
				}

		LogoSizeKpix1 ::= TEXTUAL-CONVENTION
			STATUS current
			DESCRIPTION
				"Type LOGO_SIZE_KPIX_1"
			SYNTAX INTEGER
				{
				unknown(-3),
				range-min(4),
				range-max(64)
				}

		LoudnessType ::= TEXTUAL-CONVENTION
			STATUS current
			DESCRIPTION
				"Type LOUDNESS_TYPE"
			SYNTAX INTEGER
				{
				unknown(-3),
				momentary(0),
				short-term(1),
				integrated(2),
				period(3)
				}

		LumaUint8 ::= TEXTUAL-CONVENTION
			STATUS current
			DESCRIPTION
				"Type LUMA_UINT_8"
			SYNTAX INTEGER
				{
				unknown(-3),
				range-min(1),
				range-max(255)
				}

		MadiNCh ::= TEXTUAL-CONVENTION
			STATUS current
			DESCRIPTION
				"Type MADI_N_CH"
			SYNTAX INTEGER
				{
				unknown(-3),
				sel56-channels(56),
				sel64-channels(64)
				}

		ModeFail1 ::= TEXTUAL-CONVENTION
			STATUS current
			DESCRIPTION
				"Type MODE_FAIL_1"
			SYNTAX INTEGER
				{
				unknown(-3),
				field-freeze-30s-black(0),
				black(1),
				field-freeze-reference(2)
				}

		ModuleSlot3 ::= TEXTUAL-CONVENTION
			STATUS current
			DESCRIPTION
				"Type MODULE_SLOT_3"
			SYNTAX INTEGER
				{
				unknown(-3),
				range-min(0),
				range-max(21)
				}

		Month ::= TEXTUAL-CONVENTION
			STATUS current
			DESCRIPTION
				"Type MONTH"
			SYNTAX INTEGER
				{
				unknown(-3),
				january(1),
				february(2),
				march(3),
				april(4),
				may(5),
				june(6),
				july(7),
				august(8),
				september(9),
				october(10),
				november(11),
				december(12)
				}

		MpxControl ::= TEXTUAL-CONVENTION
			STATUS current
			DESCRIPTION
				"Type MPX_CONTROL"
			SYNTAX INTEGER
				{
				unknown(-3),
				gpi(0),
				software(1)
				}

		MpxGain1 ::= TEXTUAL-CONVENTION
			STATUS current
			DESCRIPTION
				"Type MPX_GAIN1"
			SYNTAX INTEGER
				{
				unknown(-3),
				range-min(0),
				range-max(63)
				}

		MpxLevDbu ::= TEXTUAL-CONVENTION
			STATUS current
			DESCRIPTION
				"Type MPX_LEV_DBU"
			SYNTAX INTEGER
				{
				unknown(-3),
				range-min(0),
				range-max(255)
				}

		MpxLevV ::= TEXTUAL-CONVENTION
			STATUS current
			DESCRIPTION
				"Type MPX_LEV_V"
			SYNTAX INTEGER
				{
				unknown(-3),
				range-min(0),
				range-max(255)
				}

		MpxPreemp ::= TEXTUAL-CONVENTION
			STATUS current
			DESCRIPTION
				"Type MPX_PREEMP"
			SYNTAX INTEGER
				{
				unknown(-3),
				none(0),
				sel75-us(1),
				sel50-us(2)
				}

		MultichannlSel ::= TEXTUAL-CONVENTION
			STATUS current
			DESCRIPTION
				"Type MULTICHANNL_SEL"
			SYNTAX INTEGER
				{
				unknown(-3),
				normal(0),
				multichannel-a(1),
				multichannel-b(2)
				}

		OptPowerX2Uw ::= TEXTUAL-CONVENTION
			STATUS current
			DESCRIPTION
				"Type OPT_POWER_X2_UW"
			SYNTAX INTEGER
				{
				unknown(-3),
				range-min(0),
				range-max(255)
				}

		PacketNum ::= TEXTUAL-CONVENTION
			STATUS current
			DESCRIPTION
				"Type PACKET_NUM"
			SYNTAX INTEGER
				{
				unknown(-3),
				range-min(0),
				range-max(65535)
				}

		PacketRate ::= TEXTUAL-CONVENTION
			STATUS current
			DESCRIPTION
				"Type PACKET_RATE"
			SYNTAX INTEGER
				{
				unknown(-3),
				range-min(0),
				range-max(65535)
				}

		PckNullRate1 ::= TEXTUAL-CONVENTION
			STATUS current
			DESCRIPTION
				"Type PCK_NULL_RATE_1"
			SYNTAX INTEGER
				{
				unknown(-3),
				range-min(0),
				range-max(100)
				}

		PhaseCor ::= TEXTUAL-CONVENTION
			STATUS current
			DESCRIPTION
				"Type PHASE_COR"
			SYNTAX INTEGER
				{
				unknown(-3),
				range-min(0),
				range-max(255)
				}

		PowerX1W ::= TEXTUAL-CONVENTION
			STATUS current
			DESCRIPTION
				"Type POWER_X1_W"
			SYNTAX INTEGER
				{
				unknown(-3),
				range-min(0),
				range-max(255)
				}

		PpmDistrib ::= TEXTUAL-CONVENTION
			STATUS current
			DESCRIPTION
				"Type PPM_DISTRIB"
			SYNTAX INTEGER
				{
				unknown(-3),
				sel1-row(0),
				sel2-rows(1)
				}

		PreRoll ::= TEXTUAL-CONVENTION
			STATUS current
			DESCRIPTION
				"Type PRE_ROLL"
			SYNTAX INTEGER
				{
				unknown(-3),
				range-min(0),
				range-max(65535)
				}

		PreselSwMode1 ::= TEXTUAL-CONVENTION
			STATUS current
			DESCRIPTION
				"Type PRESEL_SW_MODE_1"
			SYNTAX INTEGER
				{
				unknown(-3),
				range-min(0),
				range-max(12)
				}

		PreselSwTime1 ::= TEXTUAL-CONVENTION
			STATUS current
			DESCRIPTION
				"Type PRESEL_SW_TIME_1"
			SYNTAX INTEGER
				{
				unknown(-3),
				fast(0),
				field(1),
				frame(2),
				slave(3)
				}

		PreselSwTime2 ::= TEXTUAL-CONVENTION
			STATUS current
			DESCRIPTION
				"Type PRESEL_SW_TIME_2"
			SYNTAX INTEGER
				{
				unknown(-3),
				fast(0),
				field(1)
				}

		PreselSwTime3 ::= TEXTUAL-CONVENTION
			STATUS current
			DESCRIPTION
				"Type PRESEL_SW_TIME_3"
			SYNTAX INTEGER
				{
				unknown(-3),
				fast(0),
				v-blank(1),
				slave(2)
				}

		PresetActive ::= TEXTUAL-CONVENTION
			STATUS current
			DESCRIPTION
				"Type PRESET_ACTIVE"
			SYNTAX INTEGER
				{
				unknown(-3),
				range-min(0),
				range-max(63)
				}

		PresetLoad ::= TEXTUAL-CONVENTION
			STATUS current
			DESCRIPTION
				"Type PRESET_LOAD"
			SYNTAX INTEGER
				{
				unknown(-3),
				range-min(0),
				range-max(127)
				}

		PresetRestore ::= TEXTUAL-CONVENTION
			STATUS current
			DESCRIPTION
				"Type PRESET_RESTORE"
			SYNTAX INTEGER
				{
				unknown(-3),
				range-min(0),
				range-max(31)
				}

		PresetSave ::= TEXTUAL-CONVENTION
			STATUS current
			DESCRIPTION
				"Type PRESET_SAVE"
			SYNTAX INTEGER
				{
				unknown(-3),
				range-min(0),
				range-max(255)
				}

		Preset16Active ::= TEXTUAL-CONVENTION
			STATUS current
			DESCRIPTION
				"Type PRESET16_ACTIVE"
			SYNTAX INTEGER
				{
				unknown(-3),
				range-min(0),
				range-max(255)
				}

		Preset16Default ::= TEXTUAL-CONVENTION
			STATUS current
			DESCRIPTION
				"Type PRESET16_DEFAULT"
			SYNTAX INTEGER
				{
				unknown(-3),
				range-min(0),
				range-max(255)
				}

		Preset16Load ::= TEXTUAL-CONVENTION
			STATUS current
			DESCRIPTION
				"Type PRESET16_LOAD"
			SYNTAX INTEGER
				{
				unknown(-3),
				range-min(0),
				range-max(255)
				}

		Preset16Save ::= TEXTUAL-CONVENTION
			STATUS current
			DESCRIPTION
				"Type PRESET16_SAVE"
			SYNTAX INTEGER
				{
				unknown(-3),
				range-min(0),
				range-max(255)
				}

		PsuDcInpV ::= TEXTUAL-CONVENTION
			STATUS current
			DESCRIPTION
				"Type PSU_DC_INP_V"
			SYNTAX INTEGER
				{
				unknown(-3),
				range-min(0),
				range-max(255)
				}

		PtpDelayMech ::= TEXTUAL-CONVENTION
			STATUS current
			DESCRIPTION
				"Type PTP_DELAY_MECH"
			SYNTAX INTEGER
				{
				unknown(-3),
				end-to-end(0),
				peer-to-peer(1),
				auto(2)
				}

		PtpInterval ::= TEXTUAL-CONVENTION
			STATUS current
			DESCRIPTION
				"Type PTP_INTERVAL"
			SYNTAX INTEGER
				{
				unknown(-3),
				range-min(0),
				range-max(255)
				}

		PtpProfile ::= TEXTUAL-CONVENTION
			STATUS current
			DESCRIPTION
				"Type PTP_PROFILE"
			SYNTAX INTEGER
				{
				unknown(-3),
				general(0),
				smpte-st-2059(1),
				aes67(2),
				ieee-802-1-as(3),
				smpteoraes(4),
				custom(15)
				}

		PtpState ::= TEXTUAL-CONVENTION
			STATUS current
			DESCRIPTION
				"Type PTP_STATE"
			SYNTAX INTEGER
				{
				unknown(-3),
				none(0),
				initializing(1),
				faulty(2),
				disabled(3),
				listening(4),
				pre-master(5),
				master(6),
				passive(7),
				uncalibrated(8),
				slave(9),
				grand-master(10)
				}

		PtpStatus ::= TEXTUAL-CONVENTION
			STATUS current
			DESCRIPTION
				"Type PTP_STATUS"
			SYNTAX INTEGER
				{
				unknown(-3),
				ethernet-1(0),
				ethernet-2(1)
				}

		Rate1 ::= TEXTUAL-CONVENTION
			STATUS current
			DESCRIPTION
				"Type RATE_1"
			SYNTAX INTEGER
				{
				unknown(-3),
				range-min(0),
				range-max(255)
				}

		Rate2 ::= TEXTUAL-CONVENTION
			STATUS current
			DESCRIPTION
				"Type RATE_2"
			SYNTAX INTEGER
				{
				unknown(-3),
				range-min(0),
				range-max(255)
				}

		RefSel1 ::= TEXTUAL-CONVENTION
			STATUS current
			DESCRIPTION
				"Type REF_SEL_1"
			SYNTAX INTEGER
				{
				unknown(-3),
				analog(0),
				sdi-digital(1),
				chassis(2),
				free-run(3)
				}

		RefSel2 ::= TEXTUAL-CONVENTION
			STATUS current
			DESCRIPTION
				"Type REF_SEL_2"
			SYNTAX INTEGER
				{
				unknown(-3),
				sdi-digital(1),
				chassis(2),
				free-run(3)
				}

		RfaCurrent ::= TEXTUAL-CONVENTION
			STATUS current
			DESCRIPTION
				"Type RFA_CURRENT"
			SYNTAX INTEGER
				{
				unknown(-3),
				range-min(0),
				range-max(255)
				}

		RfaVoltage ::= TEXTUAL-CONVENTION
			STATUS current
			DESCRIPTION
				"Type RFA_VOLTAGE"
			SYNTAX INTEGER
				{
				unknown(-3),
				range-min(0),
				range-max(255)
				}

		Sch1 ::= TEXTUAL-CONVENTION
			STATUS current
			DESCRIPTION
				"Type SCH_1"
			SYNTAX INTEGER
				{
				unknown(-3),
				range-min(0),
				range-max(255)
				}

		Sch2 ::= TEXTUAL-CONVENTION
			STATUS current
			DESCRIPTION
				"Type SCH_2"
			SYNTAX INTEGER
				{
				unknown(-3),
				range-min(0),
				range-max(255)
				}

		Sch3 ::= TEXTUAL-CONVENTION
			STATUS current
			DESCRIPTION
				"Type SCH_3"
			SYNTAX INTEGER
				{
				unknown(-3),
				range-min(0),
				range-max(255)
				}

		Scte104Interva ::= TEXTUAL-CONVENTION
			STATUS current
			DESCRIPTION
				"Type SCTE_104_INTERVA"
			SYNTAX INTEGER
				{
				unknown(-3),
				range-min(0),
				range-max(255)
				}

		Scte104PckType ::= TEXTUAL-CONVENTION
			STATUS current
			DESCRIPTION
				"Type SCTE104_PCK_TYPE"
			SYNTAX INTEGER
				{
				unknown(-3),
				range-min(0),
				range-max(4)
				}

		SdiHd12gFmt2 ::= TEXTUAL-CONVENTION
			STATUS current
			DESCRIPTION
				"Type SDI_HD_12G_FMT_2"
			SYNTAX INTEGER
				{
				unknown(-3),
				sel576i50(0),
				sel486i59dot94(1),
				sel1080i50(4),
				sel1080i59dot94(5),
				sel720p50(10),
				sel720p59dot94(11),
				sel1080p50(12),
				sel1080p59dot94(13),
				sel2160p50(14),
				sel2160p59dot94(15)
				}

		SdiHd12gFmt3 ::= TEXTUAL-CONVENTION
			STATUS current
			DESCRIPTION
				"Type SDI_HD_12G_FMT_3"
			SYNTAX INTEGER
				{
				unknown(-3),
				sel576i50(0),
				sel486i59dot94(1),
				sel720p50(2),
				sel720p59dot94(3),
				sel1080i50(5),
				sel1080i59dot94(6),
				sel1080p25(8),
				sel1080p29dot97(9),
				sel1080p50(10),
				sel1080p59dot94(11),
				sel2160p50(13),
				sel2160p59dot94(14)
				}

		SdiHd12gFmt4 ::= TEXTUAL-CONVENTION
			STATUS current
			DESCRIPTION
				"Type SDI_HD_12G_FMT_4"
			SYNTAX INTEGER
				{
				unknown(-3),
				sel576i50(0),
				sel486i59dot94(1),
				sel720p50(2),
				sel720p59dot94(3),
				sel1080i50(5),
				sel1080i59dot94(6),
				sel1080p50(10),
				sel1080p59dot94(11),
				sel2160p50(13),
				sel2160p59dot94(14)
				}

		SdiHd3gFmt1 ::= TEXTUAL-CONVENTION
			STATUS current
			DESCRIPTION
				"Type SDI_HD_3G_FMT_1"
			SYNTAX INTEGER
				{
				unknown(-3),
				sel576i50(0),
				sel486i59(1),
				sel720p59(2),
				sel720p29(3),
				sel720p23(4),
				sel1080i59(5),
				sel1080p29(6),
				sel1080p23(7),
				sel1080s23(8),
				sel720p60(9),
				sel720p50(10),
				sel720p30(11),
				sel720p25(12),
				sel720p24(13),
				sel1080i60(14),
				sel1080i50(15),
				sel1080p30(16),
				sel1080p25(17),
				sel1080p24(18),
				sel1080s24(19),
				sel1080p59(20),
				sel1080p60(21),
				sel1080p50(22)
				}

		SdiHd3gFmt2 ::= TEXTUAL-CONVENTION
			STATUS current
			DESCRIPTION
				"Type SDI_HD_3G_FMT_2"
			SYNTAX INTEGER
				{
				unknown(-3),
				sel576i50(0),
				sel486i59(1),
				sel720p59(2),
				sel720p29(3),
				sel720p23(4),
				sel1080i59(5),
				sel1080p29(6),
				sel1080p23(7),
				sel1080s23(8),
				sel720p60(9),
				sel720p50(10),
				sel720p30(11),
				sel720p25(12),
				sel720p24(13),
				sel1080i60(14),
				sel1080i50(15),
				sel1080p30(16),
				sel1080p25(17),
				sel1080p24(18),
				sel1080s24(19),
				sel1080p59(20),
				sel1080p60(21),
				sel1080p50(22),
				other(23)
				}

		SdiHd3gFmt3 ::= TEXTUAL-CONVENTION
			STATUS current
			DESCRIPTION
				"Type SDI_HD_3G_FMT_3"
			SYNTAX INTEGER
				{
				unknown(-3),
				sel576i50(0),
				sel486i59dot94(1),
				sel720p50(2),
				sel720p59dot94(3),
				sel1080i50(5),
				sel1080i59dot94(6),
				sel1080p25(8),
				sel1080p29dot97(9),
				sel1080p50(10),
				sel1080p59dot94(11),
				invalid(15)
				}

		SdiHd3gFmt4 ::= TEXTUAL-CONVENTION
			STATUS current
			DESCRIPTION
				"Type SDI_HD_3G_FMT_4"
			SYNTAX INTEGER
				{
				unknown(-3),
				sel576i50(0),
				sel486i59dot94(1),
				sel720p50(2),
				sel720p59dot94(3),
				sel1080i50(5),
				sel1080i59dot94(6),
				sel1080p25(8),
				sel1080p29dot97(9),
				sel1080p50(10),
				sel1080p59dot94(11),
				slave(14),
				other(15)
				}

		SdiHd3gFmt5 ::= TEXTUAL-CONVENTION
			STATUS current
			DESCRIPTION
				"Type SDI_HD_3G_FMT_5"
			SYNTAX INTEGER
				{
				unknown(-3),
				sel576i50(0),
				sel486i59dot94(1),
				sel720p50(2),
				sel720p59dot94(3),
				sel1080i50(5),
				sel1080i59dot94(6),
				sel1080p25(8),
				sel1080p29dot97(9),
				sel1080p50(10),
				sel1080p59dot94(11)
				}

		SdiHd3gFmt6 ::= TEXTUAL-CONVENTION
			STATUS current
			DESCRIPTION
				"Type SDI_HD_3G_FMT_6"
			SYNTAX INTEGER
				{
				unknown(-3),
				sel576i50(0),
				sel486i59dot94(1),
				sel720p50(2),
				sel720p59dot94(3),
				sel1080i50(5),
				sel1080i59dot94(6),
				sel1080p50(10),
				sel1080p59dot94(11)
				}

		SdiHd3gFmt7 ::= TEXTUAL-CONVENTION
			STATUS current
			DESCRIPTION
				"Type SDI_HD_3G_FMT_7"
			SYNTAX INTEGER
				{
				unknown(-3),
				sel576i50(0),
				sel486i59dot94(1),
				sel720p50(2),
				sel720p59dot94(3),
				sel1080i50(5),
				sel1080i59dot94(6),
				sel1080p50(10),
				sel1080p59dot94(11)
				}

		SdiIntSel ::= TEXTUAL-CONVENTION
			STATUS current
			DESCRIPTION
				"Type SDI_INT_SEL"
			SYNTAX INTEGER
				{
				unknown(-3),
				front-panel(0),
				backplane(1)
				}

		SelBit2 ::= TEXTUAL-CONVENTION
			STATUS current
			DESCRIPTION
				"Type SEL_BIT_2"
			SYNTAX INTEGER
				{
				unknown(-3),
				gpi1(0),
				gpi2(1),
				gpi3(2),
				gpi4(3),
				bit1(4),
				bit2(5),
				bit3(6),
				bit4(7)
				}

		SerialNo ::= TEXTUAL-CONVENTION
			STATUS current
			DESCRIPTION
				"Type SERIAL_NO"
			SYNTAX INTEGER
				{
				unknown(-3),
				range-min(0),
				range-max(65535)
				}

		SfpType ::= TEXTUAL-CONVENTION
			STATUS current
			DESCRIPTION
				"Type SFP_TYPE"
			SYNTAX INTEGER
				{
				unknown(-3),
				none(0),
				tx(1),
				rx(2),
				not-known(3)
				}

		SfpType1 ::= TEXTUAL-CONVENTION
			STATUS current
			DESCRIPTION
				"Type SFP_TYPE_1"
			SYNTAX INTEGER
				{
				unknown(-3),
				transceiver(0),
				dual-tx(1),
				dual-rx(2),
				tunknown(6),
				none(7)
				}

		SfpType2 ::= TEXTUAL-CONVENTION
			STATUS current
			DESCRIPTION
				"Type SFP_TYPE_2"
			SYNTAX INTEGER
				{
				unknown(-3),
				transceiver(0),
				tunknown(6),
				none(7)
				}

		Size3 ::= TEXTUAL-CONVENTION
			STATUS current
			DESCRIPTION
				"Type SIZE_3"
			SYNTAX INTEGER
				{
				unknown(-3),
				small(0),
				medium(1),
				large(2)
				}

		Smc2EthModeSt ::= TEXTUAL-CONVENTION
			STATUS current
			DESCRIPTION
				"Type SMC2_ETH_MODE_ST"
			SYNTAX INTEGER
				{
				unknown(-3),
				sel10mbps-hd(0),
				sel100mbps-hd(1),
				sel1gbps-hd(2),
				sel10mbps-fd(4),
				sel100mbps-fd(5),
				sel1gbps-fd(6),
				sel2dot5gbps(7),
				no-link(8)
				}

		SourceSel0 ::= TEXTUAL-CONVENTION
			STATUS current
			DESCRIPTION
				"Type SOURCE_SEL_0"
			SYNTAX INTEGER
				{
				unknown(-3),
				rx1(0),
				rx2(1)
				}

		SourceSel1 ::= TEXTUAL-CONVENTION
			STATUS current
			DESCRIPTION
				"Type SOURCE_SEL_1"
			SYNTAX INTEGER
				{
				unknown(-3),
				rx3(0),
				rx4(1)
				}

		StatusMode ::= TEXTUAL-CONVENTION
			STATUS current
			DESCRIPTION
				"Type STATUS_MODE"
			SYNTAX INTEGER
				{
				unknown(-3),
				momentary(0),
				timed(1)
				}

		SteDirControl ::= TEXTUAL-CONVENTION
			STATUS current
			DESCRIPTION
				"Type STE_DIR_CONTROL"
			SYNTAX INTEGER
				{
				unknown(-3),
				sdi-to-ip(0),
				ip-to-sdi(1)
				}

		SyncMode ::= TEXTUAL-CONVENTION
			STATUS current
			DESCRIPTION
				"Type SYNC_MODE"
			SYNTAX INTEGER
				{
				unknown(-3),
				eth1-if1(0),
				eth2-if1(1),
				auto(2)
				}

		SysError0 ::= TEXTUAL-CONVENTION
			STATUS current
			DESCRIPTION
				"Type SYS_ERROR_0"
			SYNTAX INTEGER
				{
				unknown(-3),
				ok(0)
				}

		TableAnalStat ::= TEXTUAL-CONVENTION
			STATUS current
			DESCRIPTION
				"Type TABLE_ANAL_STAT"
			SYNTAX INTEGER
				{
				unknown(-3),
				not-decoded(0),
				decoded(1)
				}

		TcModeCombo ::= TEXTUAL-CONVENTION
			STATUS current
			DESCRIPTION
				"Type TC_MODE_COMBO"
			SYNTAX INTEGER
				{
				unknown(-3),
				bridge(0),
				generator(1),
				bridge-with-offset(3)
				}

		TcSource ::= TEXTUAL-CONVENTION
			STATUS current
			DESCRIPTION
				"Type TC_SOURCE"
			SYNTAX INTEGER
				{
				unknown(-3),
				vitc(0),
				atc(1),
				ltc(2)
				}

		TcSourceShort ::= TEXTUAL-CONVENTION
			STATUS current
			DESCRIPTION
				"Type TC_SOURCE_SHORT"
			SYNTAX INTEGER
				{
				unknown(-3),
				vitc(0),
				atc(1)
				}

		TempKintex ::= TEXTUAL-CONVENTION
			STATUS current
			DESCRIPTION
				"Type TEMP_KINTEX"
			SYNTAX INTEGER
				{
				unknown(-3),
				range-min(0),
				range-max(4095)
				}

		Temperature0c1 ::= TEXTUAL-CONVENTION
			STATUS current
			DESCRIPTION
				"Type TEMPERATURE_0C_1"
			SYNTAX INTEGER
				{
				unknown(-3),
				range-min(0),
				range-max(255)
				}

		TimeH1 ::= TEXTUAL-CONVENTION
			STATUS current
			DESCRIPTION
				"Type TIME_H_1"
			SYNTAX INTEGER
				{
				unknown(-3),
				range-min(0),
				range-max(23)
				}

		TimeM1 ::= TEXTUAL-CONVENTION
			STATUS current
			DESCRIPTION
				"Type TIME_M_1"
			SYNTAX INTEGER
				{
				unknown(-3),
				range-min(0),
				range-max(59)
				}

		TimeS1 ::= TEXTUAL-CONVENTION
			STATUS current
			DESCRIPTION
				"Type TIME_S_1"
			SYNTAX INTEGER
				{
				unknown(-3),
				range-min(0),
				range-max(59)
				}

		TimeS2 ::= TEXTUAL-CONVENTION
			STATUS current
			DESCRIPTION
				"Type TIME_S_2"
			SYNTAX INTEGER
				{
				unknown(-3),
				range-min(0),
				range-max(255)
				}

		TimeS3 ::= TEXTUAL-CONVENTION
			STATUS current
			DESCRIPTION
				"Type TIME_S_3"
			SYNTAX INTEGER
				{
				unknown(-3),
				range-min(0),
				range-max(63)
				}

		TimeS4 ::= TEXTUAL-CONVENTION
			STATUS current
			DESCRIPTION
				"Type TIME_S_4"
			SYNTAX INTEGER
				{
				unknown(-3),
				range-min(0),
				range-max(65535)
				}

		TimeS6 ::= TEXTUAL-CONVENTION
			STATUS current
			DESCRIPTION
				"Type TIME_S_6"
			SYNTAX INTEGER
				{
				unknown(-3),
				range-min(0),
				range-max(16777215)
				}

		TimeX1Hour ::= TEXTUAL-CONVENTION
			STATUS current
			DESCRIPTION
				"Type TIME_X1_HOUR"
			SYNTAX INTEGER
				{
				unknown(-3),
				range-min(0),
				range-max(65535)
				}

		TimeX1Min ::= TEXTUAL-CONVENTION
			STATUS current
			DESCRIPTION
				"Type TIME_X1_MIN"
			SYNTAX INTEGER
				{
				unknown(-3),
				range-min(0),
				range-max(65535)
				}

		TimeX1Ms ::= TEXTUAL-CONVENTION
			STATUS current
			DESCRIPTION
				"Type TIME_X1_MS"
			SYNTAX INTEGER
				{
				unknown(-3),
				range-min(0),
				range-max(21)
				}

		TimeX1Ms1 ::= TEXTUAL-CONVENTION
			STATUS current
			DESCRIPTION
				"Type TIME_X1_MS_1"
			SYNTAX INTEGER
				{
				unknown(-3),
				range-min(0),
				range-max(65535)
				}

		TimeX1MsInt32 ::= TEXTUAL-CONVENTION
			STATUS current
			DESCRIPTION
				"Type TIME_X1_MS_INT32"
			SYNTAX INTEGER
				{
				unknown(-3),
				range-min(0),
				range-max(2147483647)
				}

		TimeX1Ns ::= TEXTUAL-CONVENTION
			STATUS current
			DESCRIPTION
				"Type TIME_X1_NS"
			SYNTAX INTEGER
				{
				unknown(-3),
				range-min(0),
				range-max(65535)
				}

		TimeX1Us ::= TEXTUAL-CONVENTION
			STATUS current
			DESCRIPTION
				"Type TIME_X1_US"
			SYNTAX INTEGER
				{
				unknown(-3),
				range-min(0),
				range-max(65535)
				}

		TimeX10Ms ::= TEXTUAL-CONVENTION
			STATUS current
			DESCRIPTION
				"Type TIME_X10_MS"
			SYNTAX INTEGER
				{
				unknown(-3),
				range-min(0),
				range-max(255)
				}

		TimeX10Ms2 ::= TEXTUAL-CONVENTION
			STATUS current
			DESCRIPTION
				"Type TIME_X10_MS_2"
			SYNTAX INTEGER
				{
				unknown(-3),
				range-min(0),
				range-max(65535)
				}

		TimeX100Ms ::= TEXTUAL-CONVENTION
			STATUS current
			DESCRIPTION
				"Type TIME_X100_MS"
			SYNTAX INTEGER
				{
				unknown(-3),
				range-min(0),
				range-max(15)
				}

		TimeX1p25Ns ::= TEXTUAL-CONVENTION
			STATUS current
			DESCRIPTION
				"Type TIME_X1P25_NS"
			SYNTAX INTEGER
				{
				unknown(-3),
				range-min(0),
				range-max(2147483647)
				}

		TimeX40Ms ::= TEXTUAL-CONVENTION
			STATUS current
			DESCRIPTION
				"Type TIME_X40_MS"
			SYNTAX INTEGER
				{
				unknown(-3),
				range-min(0),
				range-max(255)
				}

		TimeX50Ms ::= TEXTUAL-CONVENTION
			STATUS current
			DESCRIPTION
				"Type TIME_X50_MS"
			SYNTAX INTEGER
				{
				unknown(-3),
				range-min(0),
				range-max(255)
				}

		TtdFreq ::= TEXTUAL-CONVENTION
			STATUS current
			DESCRIPTION
				"Type TTD_FREQ"
			SYNTAX INTEGER
				{
				unknown(-3),
				range-min(0),
				range-max(65535)
				}

		TtdInput ::= TEXTUAL-CONVENTION
			STATUS current
			DESCRIPTION
				"Type TTD_INPUT"
			SYNTAX INTEGER
				{
				unknown(-3),
				input-a(0),
				input-b(1)
				}

		Ttd2Input ::= TEXTUAL-CONVENTION
			STATUS current
			DESCRIPTION
				"Type TTD2_INPUT"
			SYNTAX INTEGER
				{
				unknown(-3),
				bus(0),
				front(1)
				}

		Ttd2OutSel ::= TEXTUAL-CONVENTION
			STATUS current
			DESCRIPTION
				"Type TTD2_OUT_SEL"
			SYNTAX INTEGER
				{
				unknown(-3),
				sel10mhz(0),
				sel1pps(1)
				}

		TxtBridgeLine ::= TEXTUAL-CONVENTION
			STATUS current
			DESCRIPTION
				"Type TXT_BRIDGE_LINE"
			SYNTAX INTEGER
				{
				unknown(-3),
				range-min(0),
				range-max(31)
				}

		TxtThreshold ::= TEXTUAL-CONVENTION
			STATUS current
			DESCRIPTION
				"Type TXT_THRESHOLD"
			SYNTAX INTEGER
				{
				unknown(-3),
				range-min(0),
				range-max(255)
				}

		UbloxF9tVer ::= TEXTUAL-CONVENTION
			STATUS current
			DESCRIPTION
				"Type UBLOX_F9T_VER"
			SYNTAX INTEGER
				{
				unknown(-3),
				not-known(0),
				tim201(1),
				tim220(2)
				}

		Uint1 ::= TEXTUAL-CONVENTION
			STATUS current
			DESCRIPTION
				"Type UINT_1"
			SYNTAX INTEGER
				{
				unknown(-3),
				range-min(0),
				range-max(1)
				}

		Uint11 ::= TEXTUAL-CONVENTION
			STATUS current
			DESCRIPTION
				"Type UINT_11"
			SYNTAX INTEGER
				{
				unknown(-3),
				range-min(0),
				range-max(2047)
				}

		Uint12 ::= TEXTUAL-CONVENTION
			STATUS current
			DESCRIPTION
				"Type UINT_12"
			SYNTAX INTEGER
				{
				unknown(-3),
				range-min(0),
				range-max(4095)
				}

		Uint13 ::= TEXTUAL-CONVENTION
			STATUS current
			DESCRIPTION
				"Type UINT_13"
			SYNTAX INTEGER
				{
				unknown(-3),
				range-min(0),
				range-max(8191)
				}

		Uint16 ::= TEXTUAL-CONVENTION
			STATUS current
			DESCRIPTION
				"Type UINT_16"
			SYNTAX INTEGER
				{
				unknown(-3),
				range-min(0),
				range-max(65535)
				}

		Uint1613msb ::= TEXTUAL-CONVENTION
			STATUS current
			DESCRIPTION
				"Type UINT_16_13MSB"
			SYNTAX INTEGER
				{
				unknown(-3),
				range-min(0),
				range-max(65535)
				}

		Uint2 ::= TEXTUAL-CONVENTION
			STATUS current
			DESCRIPTION
				"Type UINT_2"
			SYNTAX INTEGER
				{
				unknown(-3),
				range-min(0),
				range-max(3)
				}

		Uint3 ::= TEXTUAL-CONVENTION
			STATUS current
			DESCRIPTION
				"Type UINT_3"
			SYNTAX INTEGER
				{
				unknown(-3),
				range-min(0),
				range-max(7)
				}

		Uint4 ::= TEXTUAL-CONVENTION
			STATUS current
			DESCRIPTION
				"Type UINT_4"
			SYNTAX INTEGER
				{
				unknown(-3),
				range-min(0),
				range-max(15)
				}

		Uint4X ::= TEXTUAL-CONVENTION
			STATUS current
			DESCRIPTION
				"Type UINT_4_X"
			SYNTAX INTEGER
				{
				unknown(-3),
				range-min(0),
				range-max(15)
				}

		Uint5 ::= TEXTUAL-CONVENTION
			STATUS current
			DESCRIPTION
				"Type UINT_5"
			SYNTAX INTEGER
				{
				unknown(-3),
				range-min(0),
				range-max(31)
				}

		Uint6 ::= TEXTUAL-CONVENTION
			STATUS current
			DESCRIPTION
				"Type UINT_6"
			SYNTAX INTEGER
				{
				unknown(-3),
				range-min(0),
				range-max(63)
				}

		Uint7 ::= TEXTUAL-CONVENTION
			STATUS current
			DESCRIPTION
				"Type UINT_7"
			SYNTAX INTEGER
				{
				unknown(-3),
				range-min(0),
				range-max(127)
				}

		Uint8 ::= TEXTUAL-CONVENTION
			STATUS current
			DESCRIPTION
				"Type UINT_8"
			SYNTAX INTEGER
				{
				unknown(-3),
				range-min(0),
				range-max(255)
				}

		Uint8X ::= TEXTUAL-CONVENTION
			STATUS current
			DESCRIPTION
				"Type UINT_8_X"
			SYNTAX INTEGER
				{
				unknown(-3),
				range-min(0),
				range-max(255)
				}

		UmidStatus ::= TEXTUAL-CONVENTION
			STATUS current
			DESCRIPTION
				"Type UMID_STATUS"
			SYNTAX INTEGER
				{
				unknown(-3),
				equal(0),
				none-present(1),
				different(2),
				only-one-present(3)
				}

		UopInput ::= TEXTUAL-CONVENTION
			STATUS current
			DESCRIPTION
				"Type UOP_INPUT"
			SYNTAX INTEGER
				{
				unknown(-3),
				none(0),
				sfp-a(1),
				sfp-b(2),
				bnc-a(3),
				bnc-b(4),
				backplane-a(5),
				backplane-b(6)
				}

		UopRate ::= TEXTUAL-CONVENTION
			STATUS current
			DESCRIPTION
				"Type UOP_RATE"
			SYNTAX INTEGER
				{
				unknown(-3),
				sel12g(0),
				sel6g(1),
				sel3g(2),
				sel1dot5g(3),
				sel270m(4),
				tunknown(7)
				}

		UvdInput ::= TEXTUAL-CONVENTION
			STATUS current
			DESCRIPTION
				"Type UVD_INPUT"
			SYNTAX INTEGER
				{
				unknown(-3),
				bnc(0),
				backplane(1)
				}

		V0SyncV2DmAu ::= TEXTUAL-CONVENTION
			STATUS current
			DESCRIPTION
				"Type V0_SYNC_V2_DM_AU"
			SYNTAX INTEGER
				{
				unknown(-3),
				range-min(0),
				range-max(3)
				}

		VbiLine ::= TEXTUAL-CONVENTION
			STATUS current
			DESCRIPTION
				"Type VBI_LINE"
			SYNTAX INTEGER
				{
				unknown(-3),
				range-min(7),
				range-max(22)
				}

		VccVoltage ::= TEXTUAL-CONVENTION
			STATUS current
			DESCRIPTION
				"Type VCC_VOLTAGE"
			SYNTAX INTEGER
				{
				unknown(-3),
				range-min(0),
				range-max(255)
				}

		VideoLine ::= TEXTUAL-CONVENTION
			STATUS current
			DESCRIPTION
				"Type VIDEO_LINE"
			SYNTAX INTEGER
				{
				unknown(-3),
				range-min(0),
				range-max(624)
				}

		VirtMode ::= TEXTUAL-CONVENTION
			STATUS current
			DESCRIPTION
				"Type VIRT_MODE"
			SYNTAX INTEGER
				{
				unknown(-3),
				range-min(0),
				range-max(7)
				}

		VitcLtc ::= TEXTUAL-CONVENTION
			STATUS current
			DESCRIPTION
				"Type VITC_LTC"
			SYNTAX INTEGER
				{
				unknown(-3),
				vitc(0),
				ltc(1)
				}

		VtrLockSrc ::= TEXTUAL-CONVENTION
			STATUS current
			DESCRIPTION
				"Type VTR_LOCK_SRC"
			SYNTAX INTEGER
				{
				unknown(-3),
				range-min(0),
				range-max(2)
				}

		VtrMeasType ::= TEXTUAL-CONVENTION
			STATUS current
			DESCRIPTION
				"Type VTR_MEAS_TYPE"
			SYNTAX INTEGER
				{
				unknown(-3),
				in1-in2(0),
				in1-timestamp(1)
				}

		Vu0Mode ::= TEXTUAL-CONVENTION
			STATUS current
			DESCRIPTION
				"Type VU_0_MODE"
			SYNTAX INTEGER
				{
				unknown(-3),
				range-min(0),
				range-max(1)
				}

		Wavelength1 ::= TEXTUAL-CONVENTION
			STATUS current
			DESCRIPTION
				"Type WAVELENGTH_1"
			SYNTAX INTEGER
				{
				unknown(-3),
				range-min(0),
				range-max(65)
				}

		WeekOfMonth ::= TEXTUAL-CONVENTION
			STATUS current
			DESCRIPTION
				"Type WEEK_OF_MONTH"
			SYNTAX INTEGER
				{
				unknown(-3),
				sel1st(1),
				sel2nd(2),
				sel3rd(3),
				sel4th(4),
				last(5)
				}

	                        
--
-- Node definitions
--
	
-- 1.3.6.1.4.1.10106
		-- 1.3.6.1.4.1.10106
		albalaRoot OBJECT-IDENTITY
			STATUS current
			DESCRIPTION 
				"Enterprise node, assigned by IANA"
			::= { enterprises 10106 }

		
--  1.3.6.1.4.1.10106.1
		-- 1.3.6.1.4.1.10106.1
		albalaReg OBJECT-IDENTITY
			STATUS current
			DESCRIPTION 
				"Registry and version information."
			::= { albalaRoot 1 }

		
--  1.3.6.1.4.1.10106.1.1
		-- 1.3.6.1.4.1.10106.1.1
		albalaModules OBJECT-IDENTITY
			STATUS current
			DESCRIPTION 
				"List of modules covered by this MIB file."
			::= { albalaReg 1 }

		
--  1.3.6.1.4.1.10106.2
		-- 1.3.6.1.4.1.10106.2
		albalaGeneric OBJECT-IDENTITY
			STATUS current
			DESCRIPTION 
				"General definitions."
			::= { albalaRoot 2 }

		
--  1.3.6.1.4.1.10106.2.1
		-- 1.3.6.1.4.1.10106.2.1
		albalaObjects OBJECT IDENTIFIER ::= { albalaGeneric 1 }

		
--  1.3.6.1.4.1.10106.2.1.2
		-- 1.3.6.1.4.1.10106.2.1.1
		albalaTraps OBJECT IDENTIFIER ::= { albalaObjects 1 }

		
--  1.3.6.1.4.1.10106.2.1.2.2
		-- 1.3.6.1.4.1.10106.2.1.1.1
		moduleStatusChange NOTIFICATION-TYPE
			OBJECTS { moduleIndex, moduleStatus }
			STATUS current
			DESCRIPTION 
				"Module status has changed."
			::= { albalaTraps 1 }

		
		-- 1.3.6.1.4.1.10106.2.1.1.2
		agentStatusChange NOTIFICATION-TYPE
			OBJECTS { trapCounter, agentStatus }
			STATUS current
			DESCRIPTION 
				"Agent status has changed."
			::= { albalaTraps 2 }
      
      
		

		-- 1.3.6.1.4.1.10106.2.1.1.125101
		vct3000p01v1Traps OBJECT IDENTIFIER ::= { albalaTraps 125101 }

		-- 1.3.6.1.4.1.10106.2.1.1.125101.3
		vct3000p01v1ModeTrap NOTIFICATION-TYPE
		OBJECTS { trapCounter, vct3000p01v1Index, vct3000p01v1Mode }
		STATUS current
		DESCRIPTION
			"Allows selecting the switching mode Trap"
		::= { vct3000p01v1Traps 3 }

		-- 1.3.6.1.4.1.10106.2.1.1.125101.3
		vct3000p01v1InputTrap NOTIFICATION-TYPE
		OBJECTS { trapCounter, vct3000p01v1Index, vct3000p01v1Input }
		STATUS current
		DESCRIPTION
			"Selected input Trap"
		::= { vct3000p01v1Traps 5 }

		-- 1.3.6.1.4.1.10106.2.1.1.125101.3
		vct3000p01v1MainFailTrap NOTIFICATION-TYPE
		OBJECTS { trapCounter, vct3000p01v1Index, vct3000p01v1MainFail }
		STATUS current
		DESCRIPTION
			"Main input status Trap"
		::= { vct3000p01v1Traps 11 }

		-- 1.3.6.1.4.1.10106.2.1.1.125101.3
		vct3000p01v1ResFailTrap NOTIFICATION-TYPE
		OBJECTS { trapCounter, vct3000p01v1Index, vct3000p01v1ResFail }
		STATUS current
		DESCRIPTION
			"Reserve input status Trap"
		::= { vct3000p01v1Traps 13 }

		-- 1.3.6.1.4.1.10106.2.1.1.126001
		vct3000c02v1Traps OBJECT IDENTIFIER ::= { albalaTraps 126001 }

		-- 1.3.6.1.4.1.10106.2.1.1.126001.3
		vct3000c02v1ModeTrap NOTIFICATION-TYPE
		OBJECTS { trapCounter, vct3000c02v1Index, vct3000c02v1Mode }
		STATUS current
		DESCRIPTION
			"Allows selecting the switching mode Trap"
		::= { vct3000c02v1Traps 3 }

		-- 1.3.6.1.4.1.10106.2.1.1.126001.3
		vct3000c02v1InputTrap NOTIFICATION-TYPE
		OBJECTS { trapCounter, vct3000c02v1Index, vct3000c02v1Input }
		STATUS current
		DESCRIPTION
			"Selected input Trap"
		::= { vct3000c02v1Traps 5 }

		-- 1.3.6.1.4.1.10106.2.1.1.126001.3
		vct3000c02v1MainFailTrap NOTIFICATION-TYPE
		OBJECTS { trapCounter, vct3000c02v1Index, vct3000c02v1MainFail }
		STATUS current
		DESCRIPTION
			"Main input status Trap"
		::= { vct3000c02v1Traps 11 }

		-- 1.3.6.1.4.1.10106.2.1.1.126001.3
		vct3000c02v1ResFailTrap NOTIFICATION-TYPE
		OBJECTS { trapCounter, vct3000c02v1Index, vct3000c02v1ResFail }
		STATUS current
		DESCRIPTION
			"Reserve input status Trap"
		::= { vct3000c02v1Traps 13 }

		-- 1.3.6.1.4.1.10106.2.1.1.126201
		vct3000c04v1Traps OBJECT IDENTIFIER ::= { albalaTraps 126201 }

		-- 1.3.6.1.4.1.10106.2.1.1.126201.3
		vct3000c04v1ModeTrap NOTIFICATION-TYPE
		OBJECTS { trapCounter, vct3000c04v1Index, vct3000c04v1Mode }
		STATUS current
		DESCRIPTION
			"Allows selecting the switching mode Trap"
		::= { vct3000c04v1Traps 3 }

		-- 1.3.6.1.4.1.10106.2.1.1.126201.3
		vct3000c04v1InputTrap NOTIFICATION-TYPE
		OBJECTS { trapCounter, vct3000c04v1Index, vct3000c04v1Input }
		STATUS current
		DESCRIPTION
			"Selected input Trap"
		::= { vct3000c04v1Traps 5 }

		-- 1.3.6.1.4.1.10106.2.1.1.126201.3
		vct3000c04v1MainFailTrap NOTIFICATION-TYPE
		OBJECTS { trapCounter, vct3000c04v1Index, vct3000c04v1MainFail }
		STATUS current
		DESCRIPTION
			"Main input status Trap"
		::= { vct3000c04v1Traps 11 }

		-- 1.3.6.1.4.1.10106.2.1.1.126201.3
		vct3000c04v1ResFailTrap NOTIFICATION-TYPE
		OBJECTS { trapCounter, vct3000c04v1Index, vct3000c04v1ResFail }
		STATUS current
		DESCRIPTION
			"Reserve input status Trap"
		::= { vct3000c04v1Traps 13 }

		-- 1.3.6.1.4.1.10106.2.1.1.126301
		vct3000c05v1Traps OBJECT IDENTIFIER ::= { albalaTraps 126301 }

		-- 1.3.6.1.4.1.10106.2.1.1.126301.3
		vct3000c05v1ModeTrap NOTIFICATION-TYPE
		OBJECTS { trapCounter, vct3000c05v1Index, vct3000c05v1Mode }
		STATUS current
		DESCRIPTION
			"Allows selecting the switching mode Trap"
		::= { vct3000c05v1Traps 3 }

		-- 1.3.6.1.4.1.10106.2.1.1.126301.3
		vct3000c05v1InputTrap NOTIFICATION-TYPE
		OBJECTS { trapCounter, vct3000c05v1Index, vct3000c05v1Input }
		STATUS current
		DESCRIPTION
			"Selected input Trap"
		::= { vct3000c05v1Traps 5 }

		-- 1.3.6.1.4.1.10106.2.1.1.126301.3
		vct3000c05v1MainFailTrap NOTIFICATION-TYPE
		OBJECTS { trapCounter, vct3000c05v1Index, vct3000c05v1MainFail }
		STATUS current
		DESCRIPTION
			"Main input status Trap"
		::= { vct3000c05v1Traps 11 }

		-- 1.3.6.1.4.1.10106.2.1.1.126301.3
		vct3000c05v1ResFailTrap NOTIFICATION-TYPE
		OBJECTS { trapCounter, vct3000c05v1Index, vct3000c05v1ResFail }
		STATUS current
		DESCRIPTION
			"Reserve input status Trap"
		::= { vct3000c05v1Traps 13 }

		-- 1.3.6.1.4.1.10106.2.1.1.128301
		dvm3000p01v1Traps OBJECT IDENTIFIER ::= { albalaTraps 128301 }

		-- 1.3.6.1.4.1.10106.2.1.1.128301.3
		dvm3000p01v1NoSigATrap NOTIFICATION-TYPE
		OBJECTS { trapCounter, dvm3000p01v1Index, dvm3000p01v1NoSigA }
		STATUS current
		DESCRIPTION
			"Input signal status Trap"
		::= { dvm3000p01v1Traps 11 }

		-- 1.3.6.1.4.1.10106.2.1.1.128301.3
		dvm3000p01v1NoSigBTrap NOTIFICATION-TYPE
		OBJECTS { trapCounter, dvm3000p01v1Index, dvm3000p01v1NoSigB }
		STATUS current
		DESCRIPTION
			"Input signal status Trap"
		::= { dvm3000p01v1Traps 15 }

		-- 1.3.6.1.4.1.10106.2.1.1.129101
		dsw3000p01v1Traps OBJECT IDENTIFIER ::= { albalaTraps 129101 }

		-- 1.3.6.1.4.1.10106.2.1.1.129101.3
		dsw3000p01v1ModeTrap NOTIFICATION-TYPE
		OBJECTS { trapCounter, dsw3000p01v1Index, dsw3000p01v1Mode }
		STATUS current
		DESCRIPTION
			"Allows selecting the switching mode Trap"
		::= { dsw3000p01v1Traps 3 }

		-- 1.3.6.1.4.1.10106.2.1.1.129101.3
		dsw3000p01v1InputTrap NOTIFICATION-TYPE
		OBJECTS { trapCounter, dsw3000p01v1Index, dsw3000p01v1Input }
		STATUS current
		DESCRIPTION
			"Selected input Trap"
		::= { dsw3000p01v1Traps 7 }

		-- 1.3.6.1.4.1.10106.2.1.1.129101.3
		dsw3000p01v1MainFailTrap NOTIFICATION-TYPE
		OBJECTS { trapCounter, dsw3000p01v1Index, dsw3000p01v1MainFail }
		STATUS current
		DESCRIPTION
			"Main input status Trap"
		::= { dsw3000p01v1Traps 9 }

		-- 1.3.6.1.4.1.10106.2.1.1.129101.3
		dsw3000p01v1ExtMainFailTrap NOTIFICATION-TYPE
		OBJECTS { trapCounter, dsw3000p01v1Index, dsw3000p01v1ExtMainFail }
		STATUS current
		DESCRIPTION
			"Main external input fail status Trap"
		::= { dsw3000p01v1Traps 11 }

		-- 1.3.6.1.4.1.10106.2.1.1.129101.3
		dsw3000p01v1ResFailTrap NOTIFICATION-TYPE
		OBJECTS { trapCounter, dsw3000p01v1Index, dsw3000p01v1ResFail }
		STATUS current
		DESCRIPTION
			"Reserve input status Trap"
		::= { dsw3000p01v1Traps 13 }

		-- 1.3.6.1.4.1.10106.2.1.1.129101.3
		dsw3000p01v1ExtResFailTrap NOTIFICATION-TYPE
		OBJECTS { trapCounter, dsw3000p01v1Index, dsw3000p01v1ExtResFail }
		STATUS current
		DESCRIPTION
			"Reserve external input fail status Trap"
		::= { dsw3000p01v1Traps 15 }

		-- 1.3.6.1.4.1.10106.2.1.1.129101.3
		dsw3000p01v1AuxFailTrap NOTIFICATION-TYPE
		OBJECTS { trapCounter, dsw3000p01v1Index, dsw3000p01v1AuxFail }
		STATUS current
		DESCRIPTION
			"Auxiliar input status Trap"
		::= { dsw3000p01v1Traps 17 }

		-- 1.3.6.1.4.1.10106.2.1.1.129101.3
		dsw3000p01v1ExtAuxFailTrap NOTIFICATION-TYPE
		OBJECTS { trapCounter, dsw3000p01v1Index, dsw3000p01v1ExtAuxFail }
		STATUS current
		DESCRIPTION
			"Auxiliar external input fail status Trap"
		::= { dsw3000p01v1Traps 19 }

		-- 1.3.6.1.4.1.10106.2.1.1.130101
		lns3000p01v1Traps OBJECT IDENTIFIER ::= { albalaTraps 130101 }

		-- 1.3.6.1.4.1.10106.2.1.1.130101.3
		lns3000p01v1NoSignalPgmTrap NOTIFICATION-TYPE
		OBJECTS { trapCounter, lns3000p01v1Index, lns3000p01v1NoSignalPgm }
		STATUS current
		DESCRIPTION
			"SDI input signal status Trap"
		::= { lns3000p01v1Traps 13 }

		-- 1.3.6.1.4.1.10106.2.1.1.130101.3
		lns3000p01v1TimingErrTrap NOTIFICATION-TYPE
		OBJECTS { trapCounter, lns3000p01v1Index, lns3000p01v1TimingErr }
		STATUS current
		DESCRIPTION
			"Indicates that the module can not operate as line sync because the timing between inputs is does not allow it Trap"
		::= { lns3000p01v1Traps 17 }

		-- 1.3.6.1.4.1.10106.2.1.1.130101.3
		lns3000p01v1NoSignalRefTrap NOTIFICATION-TYPE
		OBJECTS { trapCounter, lns3000p01v1Index, lns3000p01v1NoSignalRef }
		STATUS current
		DESCRIPTION
			"SDI input signal status Trap"
		::= { lns3000p01v1Traps 19 }

		-- 1.3.6.1.4.1.10106.2.1.1.131502
		dli3000p01v2Traps OBJECT IDENTIFIER ::= { albalaTraps 131502 }

		-- 1.3.6.1.4.1.10106.2.1.1.131502.3
		dli3000p01v2NoSigTrap NOTIFICATION-TYPE
		OBJECTS { trapCounter, dli3000p01v2Index, dli3000p01v2NoSig }
		STATUS current
		DESCRIPTION
			"Indicates no signal fail Trap"
		::= { dli3000p01v2Traps 25 }

		-- 1.3.6.1.4.1.10106.2.1.1.133501
		tly3032p01v1Traps OBJECT IDENTIFIER ::= { albalaTraps 133501 }

		-- 1.3.6.1.4.1.10106.2.1.1.133501.3
		tly3032p01v1Gpi1Trap NOTIFICATION-TYPE
		OBJECTS { trapCounter, tly3032p01v1Index, tly3032p01v1Gpi1 }
		STATUS current
		DESCRIPTION
			"GPI1 status Trap"
		::= { tly3032p01v1Traps 3 }

		-- 1.3.6.1.4.1.10106.2.1.1.133501.3
		tly3032p01v1Gpi2Trap NOTIFICATION-TYPE
		OBJECTS { trapCounter, tly3032p01v1Index, tly3032p01v1Gpi2 }
		STATUS current
		DESCRIPTION
			"GPI2 status Trap"
		::= { tly3032p01v1Traps 5 }

		-- 1.3.6.1.4.1.10106.2.1.1.133501.3
		tly3032p01v1Gpi3Trap NOTIFICATION-TYPE
		OBJECTS { trapCounter, tly3032p01v1Index, tly3032p01v1Gpi3 }
		STATUS current
		DESCRIPTION
			"GPI3 status Trap"
		::= { tly3032p01v1Traps 7 }

		-- 1.3.6.1.4.1.10106.2.1.1.133501.3
		tly3032p01v1Gpi4Trap NOTIFICATION-TYPE
		OBJECTS { trapCounter, tly3032p01v1Index, tly3032p01v1Gpi4 }
		STATUS current
		DESCRIPTION
			"GPI4 status Trap"
		::= { tly3032p01v1Traps 9 }

		-- 1.3.6.1.4.1.10106.2.1.1.133501.3
		tly3032p01v1Gpi5Trap NOTIFICATION-TYPE
		OBJECTS { trapCounter, tly3032p01v1Index, tly3032p01v1Gpi5 }
		STATUS current
		DESCRIPTION
			"GPI5 status Trap"
		::= { tly3032p01v1Traps 11 }

		-- 1.3.6.1.4.1.10106.2.1.1.133501.3
		tly3032p01v1Gpi6Trap NOTIFICATION-TYPE
		OBJECTS { trapCounter, tly3032p01v1Index, tly3032p01v1Gpi6 }
		STATUS current
		DESCRIPTION
			"GPI6 status Trap"
		::= { tly3032p01v1Traps 13 }

		-- 1.3.6.1.4.1.10106.2.1.1.133501.3
		tly3032p01v1Gpi7Trap NOTIFICATION-TYPE
		OBJECTS { trapCounter, tly3032p01v1Index, tly3032p01v1Gpi7 }
		STATUS current
		DESCRIPTION
			"GPI7 status Trap"
		::= { tly3032p01v1Traps 15 }

		-- 1.3.6.1.4.1.10106.2.1.1.133501.3
		tly3032p01v1Gpi8Trap NOTIFICATION-TYPE
		OBJECTS { trapCounter, tly3032p01v1Index, tly3032p01v1Gpi8 }
		STATUS current
		DESCRIPTION
			"GPI8 status Trap"
		::= { tly3032p01v1Traps 17 }

		-- 1.3.6.1.4.1.10106.2.1.1.133501.3
		tly3032p01v1Gpi9Trap NOTIFICATION-TYPE
		OBJECTS { trapCounter, tly3032p01v1Index, tly3032p01v1Gpi9 }
		STATUS current
		DESCRIPTION
			"GPI9 status Trap"
		::= { tly3032p01v1Traps 19 }

		-- 1.3.6.1.4.1.10106.2.1.1.133501.3
		tly3032p01v1Gpi10Trap NOTIFICATION-TYPE
		OBJECTS { trapCounter, tly3032p01v1Index, tly3032p01v1Gpi10 }
		STATUS current
		DESCRIPTION
			"GPI10 status Trap"
		::= { tly3032p01v1Traps 21 }

		-- 1.3.6.1.4.1.10106.2.1.1.133501.3
		tly3032p01v1Gpi11Trap NOTIFICATION-TYPE
		OBJECTS { trapCounter, tly3032p01v1Index, tly3032p01v1Gpi11 }
		STATUS current
		DESCRIPTION
			"GPI11 status Trap"
		::= { tly3032p01v1Traps 23 }

		-- 1.3.6.1.4.1.10106.2.1.1.133501.3
		tly3032p01v1Gpi12Trap NOTIFICATION-TYPE
		OBJECTS { trapCounter, tly3032p01v1Index, tly3032p01v1Gpi12 }
		STATUS current
		DESCRIPTION
			"GPI12 status Trap"
		::= { tly3032p01v1Traps 25 }

		-- 1.3.6.1.4.1.10106.2.1.1.133501.3
		tly3032p01v1Gpi13Trap NOTIFICATION-TYPE
		OBJECTS { trapCounter, tly3032p01v1Index, tly3032p01v1Gpi13 }
		STATUS current
		DESCRIPTION
			"GPI13 status Trap"
		::= { tly3032p01v1Traps 27 }

		-- 1.3.6.1.4.1.10106.2.1.1.133501.3
		tly3032p01v1Gpi14Trap NOTIFICATION-TYPE
		OBJECTS { trapCounter, tly3032p01v1Index, tly3032p01v1Gpi14 }
		STATUS current
		DESCRIPTION
			"GPI14 status Trap"
		::= { tly3032p01v1Traps 29 }

		-- 1.3.6.1.4.1.10106.2.1.1.133501.3
		tly3032p01v1Gpi15Trap NOTIFICATION-TYPE
		OBJECTS { trapCounter, tly3032p01v1Index, tly3032p01v1Gpi15 }
		STATUS current
		DESCRIPTION
			"GPI15 status Trap"
		::= { tly3032p01v1Traps 31 }

		-- 1.3.6.1.4.1.10106.2.1.1.133501.3
		tly3032p01v1Gpi16Trap NOTIFICATION-TYPE
		OBJECTS { trapCounter, tly3032p01v1Index, tly3032p01v1Gpi16 }
		STATUS current
		DESCRIPTION
			"GPI16 status Trap"
		::= { tly3032p01v1Traps 33 }

		-- 1.3.6.1.4.1.10106.2.1.1.133501.3
		tly3032p01v1Gpi17Trap NOTIFICATION-TYPE
		OBJECTS { trapCounter, tly3032p01v1Index, tly3032p01v1Gpi17 }
		STATUS current
		DESCRIPTION
			"GPI17 status Trap"
		::= { tly3032p01v1Traps 35 }

		-- 1.3.6.1.4.1.10106.2.1.1.133501.3
		tly3032p01v1Gpi18Trap NOTIFICATION-TYPE
		OBJECTS { trapCounter, tly3032p01v1Index, tly3032p01v1Gpi18 }
		STATUS current
		DESCRIPTION
			"GPI18 status Trap"
		::= { tly3032p01v1Traps 37 }

		-- 1.3.6.1.4.1.10106.2.1.1.133501.3
		tly3032p01v1Gpi19Trap NOTIFICATION-TYPE
		OBJECTS { trapCounter, tly3032p01v1Index, tly3032p01v1Gpi19 }
		STATUS current
		DESCRIPTION
			"GPI19 status Trap"
		::= { tly3032p01v1Traps 39 }

		-- 1.3.6.1.4.1.10106.2.1.1.133501.3
		tly3032p01v1Gpi20Trap NOTIFICATION-TYPE
		OBJECTS { trapCounter, tly3032p01v1Index, tly3032p01v1Gpi20 }
		STATUS current
		DESCRIPTION
			"GPI20 status Trap"
		::= { tly3032p01v1Traps 41 }

		-- 1.3.6.1.4.1.10106.2.1.1.133501.3
		tly3032p01v1Gpi21Trap NOTIFICATION-TYPE
		OBJECTS { trapCounter, tly3032p01v1Index, tly3032p01v1Gpi21 }
		STATUS current
		DESCRIPTION
			"GPI21 status Trap"
		::= { tly3032p01v1Traps 43 }

		-- 1.3.6.1.4.1.10106.2.1.1.133501.3
		tly3032p01v1Gpi22Trap NOTIFICATION-TYPE
		OBJECTS { trapCounter, tly3032p01v1Index, tly3032p01v1Gpi22 }
		STATUS current
		DESCRIPTION
			"GPI22 status Trap"
		::= { tly3032p01v1Traps 45 }

		-- 1.3.6.1.4.1.10106.2.1.1.133501.3
		tly3032p01v1Gpi23Trap NOTIFICATION-TYPE
		OBJECTS { trapCounter, tly3032p01v1Index, tly3032p01v1Gpi23 }
		STATUS current
		DESCRIPTION
			"GPI23 status Trap"
		::= { tly3032p01v1Traps 47 }

		-- 1.3.6.1.4.1.10106.2.1.1.133501.3
		tly3032p01v1Gpi24Trap NOTIFICATION-TYPE
		OBJECTS { trapCounter, tly3032p01v1Index, tly3032p01v1Gpi24 }
		STATUS current
		DESCRIPTION
			"GPI24 status Trap"
		::= { tly3032p01v1Traps 49 }

		-- 1.3.6.1.4.1.10106.2.1.1.133501.3
		tly3032p01v1Gpi25Trap NOTIFICATION-TYPE
		OBJECTS { trapCounter, tly3032p01v1Index, tly3032p01v1Gpi25 }
		STATUS current
		DESCRIPTION
			"GPI25 status Trap"
		::= { tly3032p01v1Traps 51 }

		-- 1.3.6.1.4.1.10106.2.1.1.133501.3
		tly3032p01v1Gpi26Trap NOTIFICATION-TYPE
		OBJECTS { trapCounter, tly3032p01v1Index, tly3032p01v1Gpi26 }
		STATUS current
		DESCRIPTION
			"GPI26 status Trap"
		::= { tly3032p01v1Traps 53 }

		-- 1.3.6.1.4.1.10106.2.1.1.133501.3
		tly3032p01v1Gpi27Trap NOTIFICATION-TYPE
		OBJECTS { trapCounter, tly3032p01v1Index, tly3032p01v1Gpi27 }
		STATUS current
		DESCRIPTION
			"GPI27 status Trap"
		::= { tly3032p01v1Traps 55 }

		-- 1.3.6.1.4.1.10106.2.1.1.133501.3
		tly3032p01v1Gpi28Trap NOTIFICATION-TYPE
		OBJECTS { trapCounter, tly3032p01v1Index, tly3032p01v1Gpi28 }
		STATUS current
		DESCRIPTION
			"GPI28 status Trap"
		::= { tly3032p01v1Traps 57 }

		-- 1.3.6.1.4.1.10106.2.1.1.133501.3
		tly3032p01v1Gpi29Trap NOTIFICATION-TYPE
		OBJECTS { trapCounter, tly3032p01v1Index, tly3032p01v1Gpi29 }
		STATUS current
		DESCRIPTION
			"GPI29 status Trap"
		::= { tly3032p01v1Traps 59 }

		-- 1.3.6.1.4.1.10106.2.1.1.133501.3
		tly3032p01v1Gpi30Trap NOTIFICATION-TYPE
		OBJECTS { trapCounter, tly3032p01v1Index, tly3032p01v1Gpi30 }
		STATUS current
		DESCRIPTION
			"GPI30 status Trap"
		::= { tly3032p01v1Traps 61 }

		-- 1.3.6.1.4.1.10106.2.1.1.133501.3
		tly3032p01v1Gpi31Trap NOTIFICATION-TYPE
		OBJECTS { trapCounter, tly3032p01v1Index, tly3032p01v1Gpi31 }
		STATUS current
		DESCRIPTION
			"GPI31 status Trap"
		::= { tly3032p01v1Traps 63 }

		-- 1.3.6.1.4.1.10106.2.1.1.133501.3
		tly3032p01v1Gpi32Trap NOTIFICATION-TYPE
		OBJECTS { trapCounter, tly3032p01v1Index, tly3032p01v1Gpi32 }
		STATUS current
		DESCRIPTION
			"GPI32 status Trap"
		::= { tly3032p01v1Traps 65 }

		-- 1.3.6.1.4.1.10106.2.1.1.134801
		aac3000p01v1Traps OBJECT IDENTIFIER ::= { albalaTraps 134801 }

		-- 1.3.6.1.4.1.10106.2.1.1.134801.3
		aac3000p01v1NoVidTrap NOTIFICATION-TYPE
		OBJECTS { trapCounter, aac3000p01v1Index, aac3000p01v1NoVid }
		STATUS current
		DESCRIPTION
			"Indicates no video reference signal Trap"
		::= { aac3000p01v1Traps 15 }

		-- 1.3.6.1.4.1.10106.2.1.1.134801.3
		aac3000p01v1NoAesTrap NOTIFICATION-TYPE
		OBJECTS { trapCounter, aac3000p01v1Index, aac3000p01v1NoAes }
		STATUS current
		DESCRIPTION
			"Indicates no AES reference signal Trap"
		::= { aac3000p01v1Traps 17 }

		-- 1.3.6.1.4.1.10106.2.1.1.134801.3
		aac3000p01v1NoWclkTrap NOTIFICATION-TYPE
		OBJECTS { trapCounter, aac3000p01v1Index, aac3000p01v1NoWclk }
		STATUS current
		DESCRIPTION
			"Indicates no Wordclock reference signal Trap"
		::= { aac3000p01v1Traps 19 }

		-- 1.3.6.1.4.1.10106.2.1.1.134801.3
		aac3000p01v1UnlockTrap NOTIFICATION-TYPE
		OBJECTS { trapCounter, aac3000p01v1Index, aac3000p01v1Unlock }
		STATUS current
		DESCRIPTION
			"Indicates AES reference unlock fail Trap"
		::= { aac3000p01v1Traps 21 }

		-- 1.3.6.1.4.1.10106.2.1.1.134801.3
		aac3000p01v1OvldS1ChaTrap NOTIFICATION-TYPE
		OBJECTS { trapCounter, aac3000p01v1Index, aac3000p01v1OvldS1Cha }
		STATUS current
		DESCRIPTION
			"Indicates streaml 1 channel A overload fail Trap"
		::= { aac3000p01v1Traps 23 }

		-- 1.3.6.1.4.1.10106.2.1.1.134801.3
		aac3000p01v1OvldS1ChbTrap NOTIFICATION-TYPE
		OBJECTS { trapCounter, aac3000p01v1Index, aac3000p01v1OvldS1Chb }
		STATUS current
		DESCRIPTION
			"Indicates streaml 1 channel B overload fail Trap"
		::= { aac3000p01v1Traps 25 }

		-- 1.3.6.1.4.1.10106.2.1.1.134801.3
		aac3000p01v1OvldS2ChaTrap NOTIFICATION-TYPE
		OBJECTS { trapCounter, aac3000p01v1Index, aac3000p01v1OvldS2Cha }
		STATUS current
		DESCRIPTION
			"Indicates streaml 2 channel A overload fail Trap"
		::= { aac3000p01v1Traps 27 }

		-- 1.3.6.1.4.1.10106.2.1.1.134801.3
		aac3000p01v1OvldS2ChbTrap NOTIFICATION-TYPE
		OBJECTS { trapCounter, aac3000p01v1Index, aac3000p01v1OvldS2Chb }
		STATUS current
		DESCRIPTION
			"Indicates streaml 2 channel B overload fail Trap"
		::= { aac3000p01v1Traps 29 }

		-- 1.3.6.1.4.1.10106.2.1.1.134901
		aem3000p01v1Traps OBJECT IDENTIFIER ::= { albalaTraps 134901 }

		-- 1.3.6.1.4.1.10106.2.1.1.134901.3
		aem3000p01v1GroupTrap NOTIFICATION-TYPE
		OBJECTS { trapCounter, aem3000p01v1Index, aem3000p01v1Group }
		STATUS current
		DESCRIPTION
			"Allows selecting the group in which the audio is embedded Trap"
		::= { aem3000p01v1Traps 11 }

		-- 1.3.6.1.4.1.10106.2.1.1.134901.3
		aem3000p01v1NoSignalTrap NOTIFICATION-TYPE
		OBJECTS { trapCounter, aem3000p01v1Index, aem3000p01v1NoSignal }
		STATUS current
		DESCRIPTION
			"SDI input signal status Trap"
		::= { aem3000p01v1Traps 43 }

		-- 1.3.6.1.4.1.10106.2.1.1.134901.3
		aem3000p01v1SilOut1Trap NOTIFICATION-TYPE
		OBJECTS { trapCounter, aem3000p01v1Index, aem3000p01v1SilOut1 }
		STATUS current
		DESCRIPTION
			"IN1 is in silence Trap"
		::= { aem3000p01v1Traps 45 }

		-- 1.3.6.1.4.1.10106.2.1.1.134901.3
		aem3000p01v1SilOut2Trap NOTIFICATION-TYPE
		OBJECTS { trapCounter, aem3000p01v1Index, aem3000p01v1SilOut2 }
		STATUS current
		DESCRIPTION
			"IN2 is in silence Trap"
		::= { aem3000p01v1Traps 47 }

		-- 1.3.6.1.4.1.10106.2.1.1.134901.3
		aem3000p01v1OvlOut1Trap NOTIFICATION-TYPE
		OBJECTS { trapCounter, aem3000p01v1Index, aem3000p01v1OvlOut1 }
		STATUS current
		DESCRIPTION
			"IN1 is overloaded Trap"
		::= { aem3000p01v1Traps 49 }

		-- 1.3.6.1.4.1.10106.2.1.1.134901.3
		aem3000p01v1OvlOut2Trap NOTIFICATION-TYPE
		OBJECTS { trapCounter, aem3000p01v1Index, aem3000p01v1OvlOut2 }
		STATUS current
		DESCRIPTION
			"IN2 is overloaded Trap"
		::= { aem3000p01v1Traps 51 }

		-- 1.3.6.1.4.1.10106.2.1.1.135801
		ade3000p01v1Traps OBJECT IDENTIFIER ::= { albalaTraps 135801 }

		-- 1.3.6.1.4.1.10106.2.1.1.135801.3
		ade3000p01v1GroupTrap NOTIFICATION-TYPE
		OBJECTS { trapCounter, ade3000p01v1Index, ade3000p01v1Group }
		STATUS current
		DESCRIPTION
			"Allows selecting the group from which the audio is deembedded Trap"
		::= { ade3000p01v1Traps 3 }

		-- 1.3.6.1.4.1.10106.2.1.1.135801.3
		ade3000p01v1NoSignalTrap NOTIFICATION-TYPE
		OBJECTS { trapCounter, ade3000p01v1Index, ade3000p01v1NoSignal }
		STATUS current
		DESCRIPTION
			"SDI input signal status Trap"
		::= { ade3000p01v1Traps 51 }

		-- 1.3.6.1.4.1.10106.2.1.1.135801.3
		ade3000p01v1NsamAes1Trap NOTIFICATION-TYPE
		OBJECTS { trapCounter, ade3000p01v1Index, ade3000p01v1NsamAes1 }
		STATUS current
		DESCRIPTION
			"Bad number of samples per frame in AES1 signal Trap"
		::= { ade3000p01v1Traps 53 }

		-- 1.3.6.1.4.1.10106.2.1.1.135801.3
		ade3000p01v1NsamAes2Trap NOTIFICATION-TYPE
		OBJECTS { trapCounter, ade3000p01v1Index, ade3000p01v1NsamAes2 }
		STATUS current
		DESCRIPTION
			"Bad number of samples per frame in AES2 signal Trap"
		::= { ade3000p01v1Traps 55 }

		-- 1.3.6.1.4.1.10106.2.1.1.135801.3
		ade3000p01v1SilOut1Trap NOTIFICATION-TYPE
		OBJECTS { trapCounter, ade3000p01v1Index, ade3000p01v1SilOut1 }
		STATUS current
		DESCRIPTION
			"OUT1 is in silence Trap"
		::= { ade3000p01v1Traps 57 }

		-- 1.3.6.1.4.1.10106.2.1.1.135801.3
		ade3000p01v1SilOut2Trap NOTIFICATION-TYPE
		OBJECTS { trapCounter, ade3000p01v1Index, ade3000p01v1SilOut2 }
		STATUS current
		DESCRIPTION
			"OUT2 is in silence Trap"
		::= { ade3000p01v1Traps 59 }

		-- 1.3.6.1.4.1.10106.2.1.1.135801.3
		ade3000p01v1OvlOut1Trap NOTIFICATION-TYPE
		OBJECTS { trapCounter, ade3000p01v1Index, ade3000p01v1OvlOut1 }
		STATUS current
		DESCRIPTION
			"OUT1 is overloaded Trap"
		::= { ade3000p01v1Traps 61 }

		-- 1.3.6.1.4.1.10106.2.1.1.135801.3
		ade3000p01v1OvlOut2Trap NOTIFICATION-TYPE
		OBJECTS { trapCounter, ade3000p01v1Index, ade3000p01v1OvlOut2 }
		STATUS current
		DESCRIPTION
			"OUT2 is overloaded Trap"
		::= { ade3000p01v1Traps 63 }

		-- 1.3.6.1.4.1.10106.2.1.1.136301
		dsw3000c02v1Traps OBJECT IDENTIFIER ::= { albalaTraps 136301 }

		-- 1.3.6.1.4.1.10106.2.1.1.136301.3
		dsw3000c02v1ModeTrap NOTIFICATION-TYPE
		OBJECTS { trapCounter, dsw3000c02v1Index, dsw3000c02v1Mode }
		STATUS current
		DESCRIPTION
			"Allows selecting the switching mode Trap"
		::= { dsw3000c02v1Traps 3 }

		-- 1.3.6.1.4.1.10106.2.1.1.136301.3
		dsw3000c02v1InputTrap NOTIFICATION-TYPE
		OBJECTS { trapCounter, dsw3000c02v1Index, dsw3000c02v1Input }
		STATUS current
		DESCRIPTION
			"Selected input Trap"
		::= { dsw3000c02v1Traps 7 }

		-- 1.3.6.1.4.1.10106.2.1.1.136301.3
		dsw3000c02v1MainFailTrap NOTIFICATION-TYPE
		OBJECTS { trapCounter, dsw3000c02v1Index, dsw3000c02v1MainFail }
		STATUS current
		DESCRIPTION
			"Main input status Trap"
		::= { dsw3000c02v1Traps 9 }

		-- 1.3.6.1.4.1.10106.2.1.1.136301.3
		dsw3000c02v1ExtMainFailTrap NOTIFICATION-TYPE
		OBJECTS { trapCounter, dsw3000c02v1Index, dsw3000c02v1ExtMainFail }
		STATUS current
		DESCRIPTION
			"Main external input fail status Trap"
		::= { dsw3000c02v1Traps 11 }

		-- 1.3.6.1.4.1.10106.2.1.1.136301.3
		dsw3000c02v1ResFailTrap NOTIFICATION-TYPE
		OBJECTS { trapCounter, dsw3000c02v1Index, dsw3000c02v1ResFail }
		STATUS current
		DESCRIPTION
			"Reserve input status Trap"
		::= { dsw3000c02v1Traps 13 }

		-- 1.3.6.1.4.1.10106.2.1.1.136301.3
		dsw3000c02v1ExtResFailTrap NOTIFICATION-TYPE
		OBJECTS { trapCounter, dsw3000c02v1Index, dsw3000c02v1ExtResFail }
		STATUS current
		DESCRIPTION
			"Reserve external input fail status Trap"
		::= { dsw3000c02v1Traps 15 }

		-- 1.3.6.1.4.1.10106.2.1.1.136301.3
		dsw3000c02v1AuxFailTrap NOTIFICATION-TYPE
		OBJECTS { trapCounter, dsw3000c02v1Index, dsw3000c02v1AuxFail }
		STATUS current
		DESCRIPTION
			"Auxiliar input status Trap"
		::= { dsw3000c02v1Traps 17 }

		-- 1.3.6.1.4.1.10106.2.1.1.136301.3
		dsw3000c02v1ExtAuxFailTrap NOTIFICATION-TYPE
		OBJECTS { trapCounter, dsw3000c02v1Index, dsw3000c02v1ExtAuxFail }
		STATUS current
		DESCRIPTION
			"Auxiliar external input fail status Trap"
		::= { dsw3000c02v1Traps 19 }

		-- 1.3.6.1.4.1.10106.2.1.1.136601
		dem3000p01v1Traps OBJECT IDENTIFIER ::= { albalaTraps 136601 }

		-- 1.3.6.1.4.1.10106.2.1.1.136601.3
		dem3000p01v1GroupATrap NOTIFICATION-TYPE
		OBJECTS { trapCounter, dem3000p01v1Index, dem3000p01v1GroupA }
		STATUS current
		DESCRIPTION
			"Allows selecting the group in which the audio is embedded Trap"
		::= { dem3000p01v1Traps 19 }

		-- 1.3.6.1.4.1.10106.2.1.1.136601.3
		dem3000p01v1GroupBTrap NOTIFICATION-TYPE
		OBJECTS { trapCounter, dem3000p01v1Index, dem3000p01v1GroupB }
		STATUS current
		DESCRIPTION
			"Allows selecting the group in which the audio is embedded Trap"
		::= { dem3000p01v1Traps 21 }

		-- 1.3.6.1.4.1.10106.2.1.1.136601.3
		dem3000p01v1NoSignalATrap NOTIFICATION-TYPE
		OBJECTS { trapCounter, dem3000p01v1Index, dem3000p01v1NoSignalA }
		STATUS current
		DESCRIPTION
			"SDI input signal status Trap"
		::= { dem3000p01v1Traps 23 }

		-- 1.3.6.1.4.1.10106.2.1.1.136601.3
		dem3000p01v1NoAes1ATrap NOTIFICATION-TYPE
		OBJECTS { trapCounter, dem3000p01v1Index, dem3000p01v1NoAes1A }
		STATUS current
		DESCRIPTION
			"AES1 input signal status Trap"
		::= { dem3000p01v1Traps 25 }

		-- 1.3.6.1.4.1.10106.2.1.1.136601.3
		dem3000p01v1UlckAes1ATrap NOTIFICATION-TYPE
		OBJECTS { trapCounter, dem3000p01v1Index, dem3000p01v1UlckAes1A }
		STATUS current
		DESCRIPTION
			"Indicates AES1 signal unlock fail Trap"
		::= { dem3000p01v1Traps 27 }

		-- 1.3.6.1.4.1.10106.2.1.1.136601.3
		dem3000p01v1NoAes2ATrap NOTIFICATION-TYPE
		OBJECTS { trapCounter, dem3000p01v1Index, dem3000p01v1NoAes2A }
		STATUS current
		DESCRIPTION
			"AES2 input signal status Trap"
		::= { dem3000p01v1Traps 29 }

		-- 1.3.6.1.4.1.10106.2.1.1.136601.3
		dem3000p01v1UlckAes2ATrap NOTIFICATION-TYPE
		OBJECTS { trapCounter, dem3000p01v1Index, dem3000p01v1UlckAes2A }
		STATUS current
		DESCRIPTION
			"Indicates AES2 signal unlock fail Trap"
		::= { dem3000p01v1Traps 31 }

		-- 1.3.6.1.4.1.10106.2.1.1.136601.3
		dem3000p01v1NoSignalBTrap NOTIFICATION-TYPE
		OBJECTS { trapCounter, dem3000p01v1Index, dem3000p01v1NoSignalB }
		STATUS current
		DESCRIPTION
			"SDI input signal status Trap"
		::= { dem3000p01v1Traps 41 }

		-- 1.3.6.1.4.1.10106.2.1.1.136601.3
		dem3000p01v1NoAes1BTrap NOTIFICATION-TYPE
		OBJECTS { trapCounter, dem3000p01v1Index, dem3000p01v1NoAes1B }
		STATUS current
		DESCRIPTION
			"AES1 input signal status Trap"
		::= { dem3000p01v1Traps 43 }

		-- 1.3.6.1.4.1.10106.2.1.1.136601.3
		dem3000p01v1UlckAes1BTrap NOTIFICATION-TYPE
		OBJECTS { trapCounter, dem3000p01v1Index, dem3000p01v1UlckAes1B }
		STATUS current
		DESCRIPTION
			"Indicates AES1 signal unlock fail Trap"
		::= { dem3000p01v1Traps 45 }

		-- 1.3.6.1.4.1.10106.2.1.1.136601.3
		dem3000p01v1NoAes2BTrap NOTIFICATION-TYPE
		OBJECTS { trapCounter, dem3000p01v1Index, dem3000p01v1NoAes2B }
		STATUS current
		DESCRIPTION
			"AES2 input signal status Trap"
		::= { dem3000p01v1Traps 47 }

		-- 1.3.6.1.4.1.10106.2.1.1.136601.3
		dem3000p01v1UlckAes2BTrap NOTIFICATION-TYPE
		OBJECTS { trapCounter, dem3000p01v1Index, dem3000p01v1UlckAes2B }
		STATUS current
		DESCRIPTION
			"Indicates AES2 signal unlock fail Trap"
		::= { dem3000p01v1Traps 49 }

		-- 1.3.6.1.4.1.10106.2.1.1.137101
		dde3000p01v1Traps OBJECT IDENTIFIER ::= { albalaTraps 137101 }

		-- 1.3.6.1.4.1.10106.2.1.1.137101.3
		dde3000p01v1GroupATrap NOTIFICATION-TYPE
		OBJECTS { trapCounter, dde3000p01v1Index, dde3000p01v1GroupA }
		STATUS current
		DESCRIPTION
			"Allows selecting the group from which the audio is deembedded Trap"
		::= { dde3000p01v1Traps 5 }

		-- 1.3.6.1.4.1.10106.2.1.1.137101.3
		dde3000p01v1GroupBTrap NOTIFICATION-TYPE
		OBJECTS { trapCounter, dde3000p01v1Index, dde3000p01v1GroupB }
		STATUS current
		DESCRIPTION
			"Allows selecting the group from which the audio is deembedded Trap"
		::= { dde3000p01v1Traps 7 }

		-- 1.3.6.1.4.1.10106.2.1.1.137101.3
		dde3000p01v1NoSignalATrap NOTIFICATION-TYPE
		OBJECTS { trapCounter, dde3000p01v1Index, dde3000p01v1NoSignalA }
		STATUS current
		DESCRIPTION
			"SDI input signal status Trap"
		::= { dde3000p01v1Traps 53 }

		-- 1.3.6.1.4.1.10106.2.1.1.137101.3
		dde3000p01v1NsamAes1ATrap NOTIFICATION-TYPE
		OBJECTS { trapCounter, dde3000p01v1Index, dde3000p01v1NsamAes1A }
		STATUS current
		DESCRIPTION
			"Bad number of samples per frame in AES1 signal Trap"
		::= { dde3000p01v1Traps 55 }

		-- 1.3.6.1.4.1.10106.2.1.1.137101.3
		dde3000p01v1NsamAes2ATrap NOTIFICATION-TYPE
		OBJECTS { trapCounter, dde3000p01v1Index, dde3000p01v1NsamAes2A }
		STATUS current
		DESCRIPTION
			"Bad number of samples per frame in AES2 signal Trap"
		::= { dde3000p01v1Traps 57 }

		-- 1.3.6.1.4.1.10106.2.1.1.137101.3
		dde3000p01v1NoSignalBTrap NOTIFICATION-TYPE
		OBJECTS { trapCounter, dde3000p01v1Index, dde3000p01v1NoSignalB }
		STATUS current
		DESCRIPTION
			"SDI input signal status Trap"
		::= { dde3000p01v1Traps 67 }

		-- 1.3.6.1.4.1.10106.2.1.1.137101.3
		dde3000p01v1NsamAes1BTrap NOTIFICATION-TYPE
		OBJECTS { trapCounter, dde3000p01v1Index, dde3000p01v1NsamAes1B }
		STATUS current
		DESCRIPTION
			"Bad number of samples per frame in AES1 signal Trap"
		::= { dde3000p01v1Traps 69 }

		-- 1.3.6.1.4.1.10106.2.1.1.137101.3
		dde3000p01v1NsamAes2BTrap NOTIFICATION-TYPE
		OBJECTS { trapCounter, dde3000p01v1Index, dde3000p01v1NsamAes2B }
		STATUS current
		DESCRIPTION
			"Bad number of samples per frame in AES2 signal Trap"
		::= { dde3000p01v1Traps 71 }

		-- 1.3.6.1.4.1.10106.2.1.1.139701
		aad3034p01v1Traps OBJECT IDENTIFIER ::= { albalaTraps 139701 }

		-- 1.3.6.1.4.1.10106.2.1.1.139701.3
		aad3034p01v1SilenceRATrap NOTIFICATION-TYPE
		OBJECTS { trapCounter, aad3034p01v1Index, aad3034p01v1SilenceRA }
		STATUS current
		DESCRIPTION
			"Right channel silence fail Trap"
		::= { aad3034p01v1Traps 25 }

		-- 1.3.6.1.4.1.10106.2.1.1.139701.3
		aad3034p01v1SilenceLATrap NOTIFICATION-TYPE
		OBJECTS { trapCounter, aad3034p01v1Index, aad3034p01v1SilenceLA }
		STATUS current
		DESCRIPTION
			"Left channel silence fail Trap"
		::= { aad3034p01v1Traps 27 }

		-- 1.3.6.1.4.1.10106.2.1.1.139701.3
		aad3034p01v1AntiphaseATrap NOTIFICATION-TYPE
		OBJECTS { trapCounter, aad3034p01v1Index, aad3034p01v1AntiphaseA }
		STATUS current
		DESCRIPTION
			"Antiphase fail Trap"
		::= { aad3034p01v1Traps 29 }

		-- 1.3.6.1.4.1.10106.2.1.1.139701.3
		aad3034p01v1OverloadRATrap NOTIFICATION-TYPE
		OBJECTS { trapCounter, aad3034p01v1Index, aad3034p01v1OverloadRA }
		STATUS current
		DESCRIPTION
			"Right channel overload fail Trap"
		::= { aad3034p01v1Traps 31 }

		-- 1.3.6.1.4.1.10106.2.1.1.139701.3
		aad3034p01v1OverloadLATrap NOTIFICATION-TYPE
		OBJECTS { trapCounter, aad3034p01v1Index, aad3034p01v1OverloadLA }
		STATUS current
		DESCRIPTION
			"Left channel overload fail Trap"
		::= { aad3034p01v1Traps 33 }

		-- 1.3.6.1.4.1.10106.2.1.1.139701.3
		aad3034p01v1OverloadRlATrap NOTIFICATION-TYPE
		OBJECTS { trapCounter, aad3034p01v1Index, aad3034p01v1OverloadRlA }
		STATUS current
		DESCRIPTION
			"Right+left channel overload fail Trap"
		::= { aad3034p01v1Traps 35 }

		-- 1.3.6.1.4.1.10106.2.1.1.139701.3
		aad3034p01v1SilenceRBTrap NOTIFICATION-TYPE
		OBJECTS { trapCounter, aad3034p01v1Index, aad3034p01v1SilenceRB }
		STATUS current
		DESCRIPTION
			"Right channel silence fail Trap"
		::= { aad3034p01v1Traps 37 }

		-- 1.3.6.1.4.1.10106.2.1.1.139701.3
		aad3034p01v1SilenceLBTrap NOTIFICATION-TYPE
		OBJECTS { trapCounter, aad3034p01v1Index, aad3034p01v1SilenceLB }
		STATUS current
		DESCRIPTION
			"Left channel silence fail Trap"
		::= { aad3034p01v1Traps 39 }

		-- 1.3.6.1.4.1.10106.2.1.1.139701.3
		aad3034p01v1AntiphaseBTrap NOTIFICATION-TYPE
		OBJECTS { trapCounter, aad3034p01v1Index, aad3034p01v1AntiphaseB }
		STATUS current
		DESCRIPTION
			"Antiphase fail Trap"
		::= { aad3034p01v1Traps 41 }

		-- 1.3.6.1.4.1.10106.2.1.1.139701.3
		aad3034p01v1OverloadRBTrap NOTIFICATION-TYPE
		OBJECTS { trapCounter, aad3034p01v1Index, aad3034p01v1OverloadRB }
		STATUS current
		DESCRIPTION
			"Right channel overload fail Trap"
		::= { aad3034p01v1Traps 43 }

		-- 1.3.6.1.4.1.10106.2.1.1.139701.3
		aad3034p01v1OverloadLBTrap NOTIFICATION-TYPE
		OBJECTS { trapCounter, aad3034p01v1Index, aad3034p01v1OverloadLB }
		STATUS current
		DESCRIPTION
			"Left channel overload fail Trap"
		::= { aad3034p01v1Traps 45 }

		-- 1.3.6.1.4.1.10106.2.1.1.139701.3
		aad3034p01v1OverloadRlBTrap NOTIFICATION-TYPE
		OBJECTS { trapCounter, aad3034p01v1Index, aad3034p01v1OverloadRlB }
		STATUS current
		DESCRIPTION
			"Right+left channel overload fail Trap"
		::= { aad3034p01v1Traps 47 }

		-- 1.3.6.1.4.1.10106.2.1.1.141201
		frs3000p01v1Traps OBJECT IDENTIFIER ::= { albalaTraps 141201 }

		-- 1.3.6.1.4.1.10106.2.1.1.141201.3
		frs3000p01v1NoRefTrap NOTIFICATION-TYPE
		OBJECTS { trapCounter, frs3000p01v1Index, frs3000p01v1NoRef }
		STATUS current
		DESCRIPTION
			"Indicates reference signal fail Trap"
		::= { frs3000p01v1Traps 31 }

		-- 1.3.6.1.4.1.10106.2.1.1.141201.3
		frs3000p01v1RefUnlockTrap NOTIFICATION-TYPE
		OBJECTS { trapCounter, frs3000p01v1Index, frs3000p01v1RefUnlock }
		STATUS current
		DESCRIPTION
			"Indicates reference signal unlock fail Trap"
		::= { frs3000p01v1Traps 33 }

		-- 1.3.6.1.4.1.10106.2.1.1.141201.3
		frs3000p01v1NoSigTrap NOTIFICATION-TYPE
		OBJECTS { trapCounter, frs3000p01v1Index, frs3000p01v1NoSig }
		STATUS current
		DESCRIPTION
			"Indicates SDI signal fail Trap"
		::= { frs3000p01v1Traps 35 }

		-- 1.3.6.1.4.1.10106.2.1.1.141201.3
		frs3000p01v1SubcarrUnlockTrap NOTIFICATION-TYPE
		OBJECTS { trapCounter, frs3000p01v1Index, frs3000p01v1SubcarrUnlock }
		STATUS current
		DESCRIPTION
			"Indicates reference input subcarrier unlock fail Trap"
		::= { frs3000p01v1Traps 37 }

		-- 1.3.6.1.4.1.10106.2.1.1.141701
		pds3000p01v1Traps OBJECT IDENTIFIER ::= { albalaTraps 141701 }

		-- 1.3.6.1.4.1.10106.2.1.1.141701.3
		pds3000p01v1NoRefTrap NOTIFICATION-TYPE
		OBJECTS { trapCounter, pds3000p01v1Index, pds3000p01v1NoRef }
		STATUS current
		DESCRIPTION
			"Reference input signal status Trap"
		::= { pds3000p01v1Traps 27 }

		-- 1.3.6.1.4.1.10106.2.1.1.141701.3
		pds3000p01v1RefUnlockTrap NOTIFICATION-TYPE
		OBJECTS { trapCounter, pds3000p01v1Index, pds3000p01v1RefUnlock }
		STATUS current
		DESCRIPTION
			"Indicates reference input unlock fail Trap"
		::= { pds3000p01v1Traps 29 }

		-- 1.3.6.1.4.1.10106.2.1.1.141701.3
		pds3000p01v1NoCcvsTrap NOTIFICATION-TYPE
		OBJECTS { trapCounter, pds3000p01v1Index, pds3000p01v1NoCcvs }
		STATUS current
		DESCRIPTION
			"Composite video signal status Trap"
		::= { pds3000p01v1Traps 31 }

		-- 1.3.6.1.4.1.10106.2.1.1.141701.3
		pds3000p01v1CcvsUnlockTrap NOTIFICATION-TYPE
		OBJECTS { trapCounter, pds3000p01v1Index, pds3000p01v1CcvsUnlock }
		STATUS current
		DESCRIPTION
			"Indicates reference composite video signal unlock fail Trap"
		::= { pds3000p01v1Traps 33 }

		-- 1.3.6.1.4.1.10106.2.1.1.141701.3
		pds3000p01v1DecOvldTrap NOTIFICATION-TYPE
		OBJECTS { trapCounter, pds3000p01v1Index, pds3000p01v1DecOvld }
		STATUS current
		DESCRIPTION
			"Indicates overload in the composite video decoder Trap"
		::= { pds3000p01v1Traps 35 }

		-- 1.3.6.1.4.1.10106.2.1.1.141701.3
		pds3000p01v1AdOvldTrap NOTIFICATION-TYPE
		OBJECTS { trapCounter, pds3000p01v1Index, pds3000p01v1AdOvld }
		STATUS current
		DESCRIPTION
			"Indicates overload in the A/D converter Trap"
		::= { pds3000p01v1Traps 39 }

		-- 1.3.6.1.4.1.10106.2.1.1.147801
		aad3024p01v1Traps OBJECT IDENTIFIER ::= { albalaTraps 147801 }

		-- 1.3.6.1.4.1.10106.2.1.1.147801.3
		aad3024p01v1SilenceRATrap NOTIFICATION-TYPE
		OBJECTS { trapCounter, aad3024p01v1Index, aad3024p01v1SilenceRA }
		STATUS current
		DESCRIPTION
			"Right channel silence fail Trap"
		::= { aad3024p01v1Traps 17 }

		-- 1.3.6.1.4.1.10106.2.1.1.147801.3
		aad3024p01v1SilenceLATrap NOTIFICATION-TYPE
		OBJECTS { trapCounter, aad3024p01v1Index, aad3024p01v1SilenceLA }
		STATUS current
		DESCRIPTION
			"Left channel silence fail Trap"
		::= { aad3024p01v1Traps 19 }

		-- 1.3.6.1.4.1.10106.2.1.1.147801.3
		aad3024p01v1AntiphaseATrap NOTIFICATION-TYPE
		OBJECTS { trapCounter, aad3024p01v1Index, aad3024p01v1AntiphaseA }
		STATUS current
		DESCRIPTION
			"Antiphase fail Trap"
		::= { aad3024p01v1Traps 21 }

		-- 1.3.6.1.4.1.10106.2.1.1.147801.3
		aad3024p01v1OverloadRATrap NOTIFICATION-TYPE
		OBJECTS { trapCounter, aad3024p01v1Index, aad3024p01v1OverloadRA }
		STATUS current
		DESCRIPTION
			"Right channel overload fail Trap"
		::= { aad3024p01v1Traps 23 }

		-- 1.3.6.1.4.1.10106.2.1.1.147801.3
		aad3024p01v1OverloadLATrap NOTIFICATION-TYPE
		OBJECTS { trapCounter, aad3024p01v1Index, aad3024p01v1OverloadLA }
		STATUS current
		DESCRIPTION
			"Left channel overload fail Trap"
		::= { aad3024p01v1Traps 25 }

		-- 1.3.6.1.4.1.10106.2.1.1.147801.3
		aad3024p01v1SilenceRBTrap NOTIFICATION-TYPE
		OBJECTS { trapCounter, aad3024p01v1Index, aad3024p01v1SilenceRB }
		STATUS current
		DESCRIPTION
			"Right channel silence fail Trap"
		::= { aad3024p01v1Traps 27 }

		-- 1.3.6.1.4.1.10106.2.1.1.147801.3
		aad3024p01v1SilenceLBTrap NOTIFICATION-TYPE
		OBJECTS { trapCounter, aad3024p01v1Index, aad3024p01v1SilenceLB }
		STATUS current
		DESCRIPTION
			"Left channel silence fail Trap"
		::= { aad3024p01v1Traps 29 }

		-- 1.3.6.1.4.1.10106.2.1.1.147801.3
		aad3024p01v1AntiphaseBTrap NOTIFICATION-TYPE
		OBJECTS { trapCounter, aad3024p01v1Index, aad3024p01v1AntiphaseB }
		STATUS current
		DESCRIPTION
			"Antiphase fail Trap"
		::= { aad3024p01v1Traps 31 }

		-- 1.3.6.1.4.1.10106.2.1.1.147801.3
		aad3024p01v1OverloadRBTrap NOTIFICATION-TYPE
		OBJECTS { trapCounter, aad3024p01v1Index, aad3024p01v1OverloadRB }
		STATUS current
		DESCRIPTION
			"Right channel overload fail Trap"
		::= { aad3024p01v1Traps 33 }

		-- 1.3.6.1.4.1.10106.2.1.1.147801.3
		aad3024p01v1OverloadLBTrap NOTIFICATION-TYPE
		OBJECTS { trapCounter, aad3024p01v1Index, aad3024p01v1OverloadLB }
		STATUS current
		DESCRIPTION
			"Left channel overload fail Trap"
		::= { aad3024p01v1Traps 35 }

		-- 1.3.6.1.4.1.10106.2.1.1.147901
		aad3014p01v1Traps OBJECT IDENTIFIER ::= { albalaTraps 147901 }

		-- 1.3.6.1.4.1.10106.2.1.1.147901.3
		aad3014p01v1SilenceRTrap NOTIFICATION-TYPE
		OBJECTS { trapCounter, aad3014p01v1Index, aad3014p01v1SilenceR }
		STATUS current
		DESCRIPTION
			"Right channel silence fail Trap"
		::= { aad3014p01v1Traps 13 }

		-- 1.3.6.1.4.1.10106.2.1.1.147901.3
		aad3014p01v1SilenceLTrap NOTIFICATION-TYPE
		OBJECTS { trapCounter, aad3014p01v1Index, aad3014p01v1SilenceL }
		STATUS current
		DESCRIPTION
			"Left channel silence fail Trap"
		::= { aad3014p01v1Traps 15 }

		-- 1.3.6.1.4.1.10106.2.1.1.147901.3
		aad3014p01v1AntiphaseTrap NOTIFICATION-TYPE
		OBJECTS { trapCounter, aad3014p01v1Index, aad3014p01v1Antiphase }
		STATUS current
		DESCRIPTION
			"Antiphase fail Trap"
		::= { aad3014p01v1Traps 17 }

		-- 1.3.6.1.4.1.10106.2.1.1.147901.3
		aad3014p01v1OverloadRTrap NOTIFICATION-TYPE
		OBJECTS { trapCounter, aad3014p01v1Index, aad3014p01v1OverloadR }
		STATUS current
		DESCRIPTION
			"Right channel overload fail Trap"
		::= { aad3014p01v1Traps 19 }

		-- 1.3.6.1.4.1.10106.2.1.1.147901.3
		aad3014p01v1OverloadLTrap NOTIFICATION-TYPE
		OBJECTS { trapCounter, aad3014p01v1Index, aad3014p01v1OverloadL }
		STATUS current
		DESCRIPTION
			"Left channel overload fail Trap"
		::= { aad3014p01v1Traps 21 }

		-- 1.3.6.1.4.1.10106.2.1.1.147901.3
		aad3014p01v1OverloadRlTrap NOTIFICATION-TYPE
		OBJECTS { trapCounter, aad3014p01v1Index, aad3014p01v1OverloadRl }
		STATUS current
		DESCRIPTION
			"Right+left channel overload fail Trap"
		::= { aad3014p01v1Traps 23 }

		-- 1.3.6.1.4.1.10106.2.1.1.147902
		aad3014c01v2Traps OBJECT IDENTIFIER ::= { albalaTraps 147902 }

		-- 1.3.6.1.4.1.10106.2.1.1.147902.3
		aad3014c01v2SilenceRTrap NOTIFICATION-TYPE
		OBJECTS { trapCounter, aad3014c01v2Index, aad3014c01v2SilenceR }
		STATUS current
		DESCRIPTION
			"Silence fail right channel Trap"
		::= { aad3014c01v2Traps 15 }

		-- 1.3.6.1.4.1.10106.2.1.1.147902.3
		aad3014c01v2SilenceLTrap NOTIFICATION-TYPE
		OBJECTS { trapCounter, aad3014c01v2Index, aad3014c01v2SilenceL }
		STATUS current
		DESCRIPTION
			"Silence fail left channel Trap"
		::= { aad3014c01v2Traps 17 }

		-- 1.3.6.1.4.1.10106.2.1.1.147902.3
		aad3014c01v2OverloadRTrap NOTIFICATION-TYPE
		OBJECTS { trapCounter, aad3014c01v2Index, aad3014c01v2OverloadR }
		STATUS current
		DESCRIPTION
			"Overload fail right channel Trap"
		::= { aad3014c01v2Traps 19 }

		-- 1.3.6.1.4.1.10106.2.1.1.147902.3
		aad3014c01v2OverloadLTrap NOTIFICATION-TYPE
		OBJECTS { trapCounter, aad3014c01v2Index, aad3014c01v2OverloadL }
		STATUS current
		DESCRIPTION
			"Overload fail left channel Trap"
		::= { aad3014c01v2Traps 21 }

		-- 1.3.6.1.4.1.10106.2.1.1.149301
		sct3000c02v1Traps OBJECT IDENTIFIER ::= { albalaTraps 149301 }

		-- 1.3.6.1.4.1.10106.2.1.1.149301.3
		sct3000c02v1ModeTrap NOTIFICATION-TYPE
		OBJECTS { trapCounter, sct3000c02v1Index, sct3000c02v1Mode }
		STATUS current
		DESCRIPTION
			"Allows selecting the switching mode Trap"
		::= { sct3000c02v1Traps 3 }

		-- 1.3.6.1.4.1.10106.2.1.1.149301.3
		sct3000c02v1InputTrap NOTIFICATION-TYPE
		OBJECTS { trapCounter, sct3000c02v1Index, sct3000c02v1Input }
		STATUS current
		DESCRIPTION
			"Selected input Trap"
		::= { sct3000c02v1Traps 5 }

		-- 1.3.6.1.4.1.10106.2.1.1.150501
		dat3000p01v1Traps OBJECT IDENTIFIER ::= { albalaTraps 150501 }

		-- 1.3.6.1.4.1.10106.2.1.1.150501.3
		dat3000p01v1LockAesTrap NOTIFICATION-TYPE
		OBJECTS { trapCounter, dat3000p01v1Index, dat3000p01v1LockAes }
		STATUS current
		DESCRIPTION
			"Indicates AES reference lock Trap"
		::= { dat3000p01v1Traps 59 }

		-- 1.3.6.1.4.1.10106.2.1.1.150501.3
		dat3000p01v1LockVidTrap NOTIFICATION-TYPE
		OBJECTS { trapCounter, dat3000p01v1Index, dat3000p01v1LockVid }
		STATUS current
		DESCRIPTION
			"Indicates video reference lock Trap"
		::= { dat3000p01v1Traps 61 }

		-- 1.3.6.1.4.1.10106.2.1.1.150501.3
		dat3000p01v1LockWclkTrap NOTIFICATION-TYPE
		OBJECTS { trapCounter, dat3000p01v1Index, dat3000p01v1LockWclk }
		STATUS current
		DESCRIPTION
			"Indicates Wordclock reference lock Trap"
		::= { dat3000p01v1Traps 63 }

		-- 1.3.6.1.4.1.10106.2.1.1.157401
		cav3000p01v1Traps OBJECT IDENTIFIER ::= { albalaTraps 157401 }

		-- 1.3.6.1.4.1.10106.2.1.1.157401.3
		cav3000p01v1NoAnalogTrap NOTIFICATION-TYPE
		OBJECTS { trapCounter, cav3000p01v1Index, cav3000p01v1NoAnalog }
		STATUS current
		DESCRIPTION
			"Analog componet video signal input status Trap"
		::= { cav3000p01v1Traps 9 }

		-- 1.3.6.1.4.1.10106.2.1.1.157401.3
		cav3000p01v1AnalogUnlockTrap NOTIFICATION-TYPE
		OBJECTS { trapCounter, cav3000p01v1Index, cav3000p01v1AnalogUnlock }
		STATUS current
		DESCRIPTION
			"Indicates analog component video signal unlock fail Trap"
		::= { cav3000p01v1Traps 11 }

		-- 1.3.6.1.4.1.10106.2.1.1.157401.3
		cav3000p01v1AnalogOvldTrap NOTIFICATION-TYPE
		OBJECTS { trapCounter, cav3000p01v1Index, cav3000p01v1AnalogOvld }
		STATUS current
		DESCRIPTION
			"Indicates overload in the A/D converter Trap"
		::= { cav3000p01v1Traps 13 }

		-- 1.3.6.1.4.1.10106.2.1.1.157501
		cav3001p01v1Traps OBJECT IDENTIFIER ::= { albalaTraps 157501 }

		-- 1.3.6.1.4.1.10106.2.1.1.157501.3
		cav3001p01v1NoSdiTrap NOTIFICATION-TYPE
		OBJECTS { trapCounter, cav3001p01v1Index, cav3001p01v1NoSdi }
		STATUS current
		DESCRIPTION
			"SDI input signal status Trap"
		::= { cav3001p01v1Traps 7 }

		-- 1.3.6.1.4.1.10106.2.1.1.157501.3
		cav3001p01v1SdiUnlockTrap NOTIFICATION-TYPE
		OBJECTS { trapCounter, cav3001p01v1Index, cav3001p01v1SdiUnlock }
		STATUS current
		DESCRIPTION
			"Indicates SDI signal unlock fail Trap"
		::= { cav3001p01v1Traps 9 }

		-- 1.3.6.1.4.1.10106.2.1.1.157501.3
		cav3001p01v1EdhFullErrTrap NOTIFICATION-TYPE
		OBJECTS { trapCounter, cav3001p01v1Index, cav3001p01v1EdhFullErr }
		STATUS current
		DESCRIPTION
			"Full field EDH error status Trap"
		::= { cav3001p01v1Traps 13 }

		-- 1.3.6.1.4.1.10106.2.1.1.157501.3
		cav3001p01v1EdhActErrTrap NOTIFICATION-TYPE
		OBJECTS { trapCounter, cav3001p01v1Index, cav3001p01v1EdhActErr }
		STATUS current
		DESCRIPTION
			"Active picture EDH error status Trap"
		::= { cav3001p01v1Traps 15 }

		-- 1.3.6.1.4.1.10106.2.1.1.157601
		cav3002p01v1Traps OBJECT IDENTIFIER ::= { albalaTraps 157601 }

		-- 1.3.6.1.4.1.10106.2.1.1.157601.3
		cav3002p01v1NoAnalogTrap NOTIFICATION-TYPE
		OBJECTS { trapCounter, cav3002p01v1Index, cav3002p01v1NoAnalog }
		STATUS current
		DESCRIPTION
			"Analog componet video signal input status Trap"
		::= { cav3002p01v1Traps 13 }

		-- 1.3.6.1.4.1.10106.2.1.1.157601.3
		cav3002p01v1AnalogUnlockTrap NOTIFICATION-TYPE
		OBJECTS { trapCounter, cav3002p01v1Index, cav3002p01v1AnalogUnlock }
		STATUS current
		DESCRIPTION
			"Indicates analog component video signal unlock fail Trap"
		::= { cav3002p01v1Traps 15 }

		-- 1.3.6.1.4.1.10106.2.1.1.157601.3
		cav3002p01v1AnalogOvldTrap NOTIFICATION-TYPE
		OBJECTS { trapCounter, cav3002p01v1Index, cav3002p01v1AnalogOvld }
		STATUS current
		DESCRIPTION
			"Indicates overload in the A/D converter Trap"
		::= { cav3002p01v1Traps 17 }

		-- 1.3.6.1.4.1.10106.2.1.1.157601.3
		cav3002p01v1NoSdiTrap NOTIFICATION-TYPE
		OBJECTS { trapCounter, cav3002p01v1Index, cav3002p01v1NoSdi }
		STATUS current
		DESCRIPTION
			"SDI input signal status Trap"
		::= { cav3002p01v1Traps 21 }

		-- 1.3.6.1.4.1.10106.2.1.1.157601.3
		cav3002p01v1SdiUnlockTrap NOTIFICATION-TYPE
		OBJECTS { trapCounter, cav3002p01v1Index, cav3002p01v1SdiUnlock }
		STATUS current
		DESCRIPTION
			"Indicates SDI signal unlock fail Trap"
		::= { cav3002p01v1Traps 23 }

		-- 1.3.6.1.4.1.10106.2.1.1.157601.3
		cav3002p01v1EdhFullErrTrap NOTIFICATION-TYPE
		OBJECTS { trapCounter, cav3002p01v1Index, cav3002p01v1EdhFullErr }
		STATUS current
		DESCRIPTION
			"Full field EDH error status Trap"
		::= { cav3002p01v1Traps 27 }

		-- 1.3.6.1.4.1.10106.2.1.1.157601.3
		cav3002p01v1EdhActErrTrap NOTIFICATION-TYPE
		OBJECTS { trapCounter, cav3002p01v1Index, cav3002p01v1EdhActErr }
		STATUS current
		DESCRIPTION
			"Active picture EDH error status Trap"
		::= { cav3002p01v1Traps 29 }

		-- 1.3.6.1.4.1.10106.2.1.1.162801
		dsw3000c03v1Traps OBJECT IDENTIFIER ::= { albalaTraps 162801 }

		-- 1.3.6.1.4.1.10106.2.1.1.162801.3
		dsw3000c03v1ModeTrap NOTIFICATION-TYPE
		OBJECTS { trapCounter, dsw3000c03v1Index, dsw3000c03v1Mode }
		STATUS current
		DESCRIPTION
			"Allows selecting the switching mode Trap"
		::= { dsw3000c03v1Traps 3 }

		-- 1.3.6.1.4.1.10106.2.1.1.162801.3
		dsw3000c03v1InputTrap NOTIFICATION-TYPE
		OBJECTS { trapCounter, dsw3000c03v1Index, dsw3000c03v1Input }
		STATUS current
		DESCRIPTION
			"Selected input Trap"
		::= { dsw3000c03v1Traps 7 }

		-- 1.3.6.1.4.1.10106.2.1.1.162801.3
		dsw3000c03v1MainFailTrap NOTIFICATION-TYPE
		OBJECTS { trapCounter, dsw3000c03v1Index, dsw3000c03v1MainFail }
		STATUS current
		DESCRIPTION
			"Main input status Trap"
		::= { dsw3000c03v1Traps 9 }

		-- 1.3.6.1.4.1.10106.2.1.1.162801.3
		dsw3000c03v1ExtMainFailTrap NOTIFICATION-TYPE
		OBJECTS { trapCounter, dsw3000c03v1Index, dsw3000c03v1ExtMainFail }
		STATUS current
		DESCRIPTION
			"Main external input fail status Trap"
		::= { dsw3000c03v1Traps 11 }

		-- 1.3.6.1.4.1.10106.2.1.1.162801.3
		dsw3000c03v1ResFailTrap NOTIFICATION-TYPE
		OBJECTS { trapCounter, dsw3000c03v1Index, dsw3000c03v1ResFail }
		STATUS current
		DESCRIPTION
			"Reserve input status Trap"
		::= { dsw3000c03v1Traps 13 }

		-- 1.3.6.1.4.1.10106.2.1.1.162801.3
		dsw3000c03v1ExtResFailTrap NOTIFICATION-TYPE
		OBJECTS { trapCounter, dsw3000c03v1Index, dsw3000c03v1ExtResFail }
		STATUS current
		DESCRIPTION
			"Reserve external input fail status Trap"
		::= { dsw3000c03v1Traps 15 }

		-- 1.3.6.1.4.1.10106.2.1.1.162801.3
		dsw3000c03v1AuxFailTrap NOTIFICATION-TYPE
		OBJECTS { trapCounter, dsw3000c03v1Index, dsw3000c03v1AuxFail }
		STATUS current
		DESCRIPTION
			"Auxiliar input status Trap"
		::= { dsw3000c03v1Traps 17 }

		-- 1.3.6.1.4.1.10106.2.1.1.162801.3
		dsw3000c03v1ExtAuxFailTrap NOTIFICATION-TYPE
		OBJECTS { trapCounter, dsw3000c03v1Index, dsw3000c03v1ExtAuxFail }
		STATUS current
		DESCRIPTION
			"Auxiliar external input fail status Trap"
		::= { dsw3000c03v1Traps 19 }

		-- 1.3.6.1.4.1.10106.2.1.1.163501
		eap3000p01v1Traps OBJECT IDENTIFIER ::= { albalaTraps 163501 }

		-- 1.3.6.1.4.1.10106.2.1.1.163501.3
		eap3000p01v1NoSigTrap NOTIFICATION-TYPE
		OBJECTS { trapCounter, eap3000p01v1Index, eap3000p01v1NoSig }
		STATUS current
		DESCRIPTION
			"SDI input signal status Trap"
		::= { eap3000p01v1Traps 75 }

		-- 1.3.6.1.4.1.10106.2.1.1.163501.3
		eap3000p01v1Antiph12Trap NOTIFICATION-TYPE
		OBJECTS { trapCounter, eap3000p01v1Index, eap3000p01v1Antiph12 }
		STATUS current
		DESCRIPTION
			"Antiphase fail Ch.1-Ch.2 Trap"
		::= { eap3000p01v1Traps 105 }

		-- 1.3.6.1.4.1.10106.2.1.1.163501.3
		eap3000p01v1Antiph34Trap NOTIFICATION-TYPE
		OBJECTS { trapCounter, eap3000p01v1Index, eap3000p01v1Antiph34 }
		STATUS current
		DESCRIPTION
			"Antiphase fail Ch.3-Ch.4 Trap"
		::= { eap3000p01v1Traps 107 }

		-- 1.3.6.1.4.1.10106.2.1.1.163501.3
		eap3000p01v1SilCh1Trap NOTIFICATION-TYPE
		OBJECTS { trapCounter, eap3000p01v1Index, eap3000p01v1SilCh1 }
		STATUS current
		DESCRIPTION
			"Channel 1 silence Trap"
		::= { eap3000p01v1Traps 109 }

		-- 1.3.6.1.4.1.10106.2.1.1.163501.3
		eap3000p01v1SilCh2Trap NOTIFICATION-TYPE
		OBJECTS { trapCounter, eap3000p01v1Index, eap3000p01v1SilCh2 }
		STATUS current
		DESCRIPTION
			"Channel 2 silence Trap"
		::= { eap3000p01v1Traps 111 }

		-- 1.3.6.1.4.1.10106.2.1.1.163501.3
		eap3000p01v1SilCh3Trap NOTIFICATION-TYPE
		OBJECTS { trapCounter, eap3000p01v1Index, eap3000p01v1SilCh3 }
		STATUS current
		DESCRIPTION
			"Channel 3 silence Trap"
		::= { eap3000p01v1Traps 113 }

		-- 1.3.6.1.4.1.10106.2.1.1.163501.3
		eap3000p01v1SilCh4Trap NOTIFICATION-TYPE
		OBJECTS { trapCounter, eap3000p01v1Index, eap3000p01v1SilCh4 }
		STATUS current
		DESCRIPTION
			"Channel 4 silence Trap"
		::= { eap3000p01v1Traps 115 }

		-- 1.3.6.1.4.1.10106.2.1.1.163501.3
		eap3000p01v1OvlCh1Trap NOTIFICATION-TYPE
		OBJECTS { trapCounter, eap3000p01v1Index, eap3000p01v1OvlCh1 }
		STATUS current
		DESCRIPTION
			"Channel 1 overload Trap"
		::= { eap3000p01v1Traps 117 }

		-- 1.3.6.1.4.1.10106.2.1.1.163501.3
		eap3000p01v1OvlCh2Trap NOTIFICATION-TYPE
		OBJECTS { trapCounter, eap3000p01v1Index, eap3000p01v1OvlCh2 }
		STATUS current
		DESCRIPTION
			"Channel 2 overload Trap"
		::= { eap3000p01v1Traps 119 }

		-- 1.3.6.1.4.1.10106.2.1.1.163501.3
		eap3000p01v1OvlCh3Trap NOTIFICATION-TYPE
		OBJECTS { trapCounter, eap3000p01v1Index, eap3000p01v1OvlCh3 }
		STATUS current
		DESCRIPTION
			"Channel 3 overload Trap"
		::= { eap3000p01v1Traps 121 }

		-- 1.3.6.1.4.1.10106.2.1.1.163501.3
		eap3000p01v1OvlCh4Trap NOTIFICATION-TYPE
		OBJECTS { trapCounter, eap3000p01v1Index, eap3000p01v1OvlCh4 }
		STATUS current
		DESCRIPTION
			"Channel 4 overload Trap"
		::= { eap3000p01v1Traps 123 }

		-- 1.3.6.1.4.1.10106.2.1.1.166801
		txe3000p01v1Traps OBJECT IDENTIFIER ::= { albalaTraps 166801 }

		-- 1.3.6.1.4.1.10106.2.1.1.166801.3
		txe3000p01v1NoSignalTrap NOTIFICATION-TYPE
		OBJECTS { trapCounter, txe3000p01v1Index, txe3000p01v1NoSignal }
		STATUS current
		DESCRIPTION
			"SDI input signal status Trap"
		::= { txe3000p01v1Traps 17 }

		-- 1.3.6.1.4.1.10106.2.1.1.166802
		txe3000p01v2Traps OBJECT IDENTIFIER ::= { albalaTraps 166802 }

		-- 1.3.6.1.4.1.10106.2.1.1.166802.3
		txe3000p01v2NoSignalTrap NOTIFICATION-TYPE
		OBJECTS { trapCounter, txe3000p01v2Index, txe3000p01v2NoSignal }
		STATUS current
		DESCRIPTION
			"SDI input signal status Trap"
		::= { txe3000p01v2Traps 19 }

		-- 1.3.6.1.4.1.10106.2.1.1.166901
		txd3000p01v1Traps OBJECT IDENTIFIER ::= { albalaTraps 166901 }

		-- 1.3.6.1.4.1.10106.2.1.1.166901.3
		txd3000p01v1NoSignalTrap NOTIFICATION-TYPE
		OBJECTS { trapCounter, txd3000p01v1Index, txd3000p01v1NoSignal }
		STATUS current
		DESCRIPTION
			"SDI input signal status Trap"
		::= { txd3000p01v1Traps 21 }

		-- 1.3.6.1.4.1.10106.2.1.1.166902
		txd3000p01v2Traps OBJECT IDENTIFIER ::= { albalaTraps 166902 }

		-- 1.3.6.1.4.1.10106.2.1.1.166902.3
		txd3000p01v2NoSignalTrap NOTIFICATION-TYPE
		OBJECTS { trapCounter, txd3000p01v2Index, txd3000p01v2NoSignal }
		STATUS current
		DESCRIPTION
			"SDI input signal status Trap"
		::= { txd3000p01v2Traps 21 }

		-- 1.3.6.1.4.1.10106.2.1.1.167201
		vfd3000c01v1Traps OBJECT IDENTIFIER ::= { albalaTraps 167201 }

		-- 1.3.6.1.4.1.10106.2.1.1.167201.3
		vfd3000c01v1MainOutInputTrap NOTIFICATION-TYPE
		OBJECTS { trapCounter, vfd3000c01v1Index, vfd3000c01v1MainOutInput }
		STATUS current
		DESCRIPTION
			"Selected input on main out Trap"
		::= { vfd3000c01v1Traps 3 }

		-- 1.3.6.1.4.1.10106.2.1.1.167201.3
		vfd3000c01v1OutInputTrap NOTIFICATION-TYPE
		OBJECTS { trapCounter, vfd3000c01v1Index, vfd3000c01v1OutInput }
		STATUS current
		DESCRIPTION
			"Selected input on out Trap"
		::= { vfd3000c01v1Traps 5 }

		-- 1.3.6.1.4.1.10106.2.1.1.167201.3
		vfd3000c01v1MaxEqMTrap NOTIFICATION-TYPE
		OBJECTS { trapCounter, vfd3000c01v1Index, vfd3000c01v1MaxEqM }
		STATUS current
		DESCRIPTION
			"Indicates maximum equalization fail Trap"
		::= { vfd3000c01v1Traps 79 }

		-- 1.3.6.1.4.1.10106.2.1.1.167201.3
		vfd3000c01v1BadFmtMTrap NOTIFICATION-TYPE
		OBJECTS { trapCounter, vfd3000c01v1Index, vfd3000c01v1BadFmtM }
		STATUS current
		DESCRIPTION
			"Indicates bad SDI format fail Trap"
		::= { vfd3000c01v1Traps 81 }

		-- 1.3.6.1.4.1.10106.2.1.1.167201.3
		vfd3000c01v1EdhErrMTrap NOTIFICATION-TYPE
		OBJECTS { trapCounter, vfd3000c01v1Index, vfd3000c01v1EdhErrM }
		STATUS current
		DESCRIPTION
			"Indicates EDH error fail Trap"
		::= { vfd3000c01v1Traps 83 }

		-- 1.3.6.1.4.1.10106.2.1.1.167201.3
		vfd3000c01v1BlackMTrap NOTIFICATION-TYPE
		OBJECTS { trapCounter, vfd3000c01v1Index, vfd3000c01v1BlackM }
		STATUS current
		DESCRIPTION
			"Indicates black pattern fail Trap"
		::= { vfd3000c01v1Traps 85 }

		-- 1.3.6.1.4.1.10106.2.1.1.167201.3
		vfd3000c01v1FreezeMTrap NOTIFICATION-TYPE
		OBJECTS { trapCounter, vfd3000c01v1Index, vfd3000c01v1FreezeM }
		STATUS current
		DESCRIPTION
			"Indicates freeze image fail Trap"
		::= { vfd3000c01v1Traps 87 }

		-- 1.3.6.1.4.1.10106.2.1.1.167201.3
		vfd3000c01v1MaxEqRTrap NOTIFICATION-TYPE
		OBJECTS { trapCounter, vfd3000c01v1Index, vfd3000c01v1MaxEqR }
		STATUS current
		DESCRIPTION
			"Indicates maximum equalization fail Trap"
		::= { vfd3000c01v1Traps 89 }

		-- 1.3.6.1.4.1.10106.2.1.1.167201.3
		vfd3000c01v1BadFmtRTrap NOTIFICATION-TYPE
		OBJECTS { trapCounter, vfd3000c01v1Index, vfd3000c01v1BadFmtR }
		STATUS current
		DESCRIPTION
			"Indicates bad SDI format fail Trap"
		::= { vfd3000c01v1Traps 91 }

		-- 1.3.6.1.4.1.10106.2.1.1.167201.3
		vfd3000c01v1EdhErrRTrap NOTIFICATION-TYPE
		OBJECTS { trapCounter, vfd3000c01v1Index, vfd3000c01v1EdhErrR }
		STATUS current
		DESCRIPTION
			"Indicates EDH error fail Trap"
		::= { vfd3000c01v1Traps 93 }

		-- 1.3.6.1.4.1.10106.2.1.1.167201.3
		vfd3000c01v1BlackRTrap NOTIFICATION-TYPE
		OBJECTS { trapCounter, vfd3000c01v1Index, vfd3000c01v1BlackR }
		STATUS current
		DESCRIPTION
			"Indicates black pattern fail Trap"
		::= { vfd3000c01v1Traps 95 }

		-- 1.3.6.1.4.1.10106.2.1.1.167201.3
		vfd3000c01v1FreezeRTrap NOTIFICATION-TYPE
		OBJECTS { trapCounter, vfd3000c01v1Index, vfd3000c01v1FreezeR }
		STATUS current
		DESCRIPTION
			"Indicates freeze image fail Trap"
		::= { vfd3000c01v1Traps 97 }

		-- 1.3.6.1.4.1.10106.2.1.1.167501
		dar3000p01v1Traps OBJECT IDENTIFIER ::= { albalaTraps 167501 }

		-- 1.3.6.1.4.1.10106.2.1.1.167501.3
		dar3000p01v1UnlockAesTrap NOTIFICATION-TYPE
		OBJECTS { trapCounter, dar3000p01v1Index, dar3000p01v1UnlockAes }
		STATUS current
		DESCRIPTION
			"Indicates AES reference unlock fail Trap"
		::= { dar3000p01v1Traps 27 }

		-- 1.3.6.1.4.1.10106.2.1.1.167501.3
		dar3000p01v1UnlockVidTrap NOTIFICATION-TYPE
		OBJECTS { trapCounter, dar3000p01v1Index, dar3000p01v1UnlockVid }
		STATUS current
		DESCRIPTION
			"Indicates video reference unlock fail Trap"
		::= { dar3000p01v1Traps 29 }

		-- 1.3.6.1.4.1.10106.2.1.1.167501.3
		dar3000p01v1UnlockWclkTrap NOTIFICATION-TYPE
		OBJECTS { trapCounter, dar3000p01v1Index, dar3000p01v1UnlockWclk }
		STATUS current
		DESCRIPTION
			"Indicates Wordclock reference unlock fail Trap"
		::= { dar3000p01v1Traps 31 }

		-- 1.3.6.1.4.1.10106.2.1.1.167501.3
		dar3000p01v1NoAesTrap NOTIFICATION-TYPE
		OBJECTS { trapCounter, dar3000p01v1Index, dar3000p01v1NoAes }
		STATUS current
		DESCRIPTION
			"Indicates no AES reference signal Trap"
		::= { dar3000p01v1Traps 33 }

		-- 1.3.6.1.4.1.10106.2.1.1.167501.3
		dar3000p01v1NoVidTrap NOTIFICATION-TYPE
		OBJECTS { trapCounter, dar3000p01v1Index, dar3000p01v1NoVid }
		STATUS current
		DESCRIPTION
			"Indicates no video reference signal Trap"
		::= { dar3000p01v1Traps 35 }

		-- 1.3.6.1.4.1.10106.2.1.1.167501.3
		dar3000p01v1NoWclkTrap NOTIFICATION-TYPE
		OBJECTS { trapCounter, dar3000p01v1Index, dar3000p01v1NoWclk }
		STATUS current
		DESCRIPTION
			"Indicates no Wordclock reference signal Trap"
		::= { dar3000p01v1Traps 37 }

		-- 1.3.6.1.4.1.10106.2.1.1.184801
		txt3000p01v1Traps OBJECT IDENTIFIER ::= { albalaTraps 184801 }

		-- 1.3.6.1.4.1.10106.2.1.1.184801.3
		txt3000p01v1NoSigPgmTrap NOTIFICATION-TYPE
		OBJECTS { trapCounter, txt3000p01v1Index, txt3000p01v1NoSigPgm }
		STATUS current
		DESCRIPTION
			"SDI input signal status Trap"
		::= { txt3000p01v1Traps 7 }

		-- 1.3.6.1.4.1.10106.2.1.1.184801.3
		txt3000p01v1NoSigSrcTrap NOTIFICATION-TYPE
		OBJECTS { trapCounter, txt3000p01v1Index, txt3000p01v1NoSigSrc }
		STATUS current
		DESCRIPTION
			"SDI input signal status Trap"
		::= { txt3000p01v1Traps 13 }

		-- 1.3.6.1.4.1.10106.2.1.1.195701
		gps3000p01v1Traps OBJECT IDENTIFIER ::= { albalaTraps 195701 }

		-- 1.3.6.1.4.1.10106.2.1.1.195701.3
		gps3000p01v1HoldoverTrap NOTIFICATION-TYPE
		OBJECTS { trapCounter, gps3000p01v1Index, gps3000p01v1Holdover }
		STATUS current
		DESCRIPTION
			"Allows setting the module in the holdover mode Trap"
		::= { gps3000p01v1Traps 3 }

		-- 1.3.6.1.4.1.10106.2.1.1.195701.3
		gps3000p01v1HoldoverStatTrap NOTIFICATION-TYPE
		OBJECTS { trapCounter, gps3000p01v1Index, gps3000p01v1HoldoverStat }
		STATUS current
		DESCRIPTION
			"Indicates if the module is locked to GPS or to reference or it is in holdover mode Trap"
		::= { gps3000p01v1Traps 21 }

		-- 1.3.6.1.4.1.10106.2.1.1.195701.3
		gps3000p01v1RedundFailTrap NOTIFICATION-TYPE
		OBJECTS { trapCounter, gps3000p01v1Index, gps3000p01v1RedundFail }
		STATUS current
		DESCRIPTION
			"Indicates if there is any active module in the redundance system Trap"
		::= { gps3000p01v1Traps 23 }

		-- 1.3.6.1.4.1.10106.2.1.1.195701.3
		gps3000p01v1OutputsMutedTrap NOTIFICATION-TYPE
		OBJECTS { trapCounter, gps3000p01v1Index, gps3000p01v1OutputsMuted }
		STATUS current
		DESCRIPTION
			"Indicates f the module outputs are active Trap"
		::= { gps3000p01v1Traps 25 }

		-- 1.3.6.1.4.1.10106.2.1.1.195701.3
		gps3000p01v1AntenaStatTrap NOTIFICATION-TYPE
		OBJECTS { trapCounter, gps3000p01v1Index, gps3000p01v1AntenaStat }
		STATUS current
		DESCRIPTION
			"Antenna connection status Trap"
		::= { gps3000p01v1Traps 29 }

		-- 1.3.6.1.4.1.10106.2.1.1.195702
		gps3000p01v2Traps OBJECT IDENTIFIER ::= { albalaTraps 195702 }

		-- 1.3.6.1.4.1.10106.2.1.1.195702.3
		gps3000p01v2HoldoverTrap NOTIFICATION-TYPE
		OBJECTS { trapCounter, gps3000p01v2Index, gps3000p01v2Holdover }
		STATUS current
		DESCRIPTION
			"Allows setting the module in the holdover mode Trap"
		::= { gps3000p01v2Traps 3 }

		-- 1.3.6.1.4.1.10106.2.1.1.195702.3
		gps3000p01v2HoldoverStatTrap NOTIFICATION-TYPE
		OBJECTS { trapCounter, gps3000p01v2Index, gps3000p01v2HoldoverStat }
		STATUS current
		DESCRIPTION
			"Indicates if the module is locked to GPS or to reference or it is in holdover mode Trap"
		::= { gps3000p01v2Traps 21 }

		-- 1.3.6.1.4.1.10106.2.1.1.195702.3
		gps3000p01v2RedundFailTrap NOTIFICATION-TYPE
		OBJECTS { trapCounter, gps3000p01v2Index, gps3000p01v2RedundFail }
		STATUS current
		DESCRIPTION
			"Indicates if there is any active module in the redundance system Trap"
		::= { gps3000p01v2Traps 23 }

		-- 1.3.6.1.4.1.10106.2.1.1.195702.3
		gps3000p01v2OutputsMutedTrap NOTIFICATION-TYPE
		OBJECTS { trapCounter, gps3000p01v2Index, gps3000p01v2OutputsMuted }
		STATUS current
		DESCRIPTION
			"Indicates f the module outputs are active Trap"
		::= { gps3000p01v2Traps 25 }

		-- 1.3.6.1.4.1.10106.2.1.1.195702.3
		gps3000p01v2AntenaStatTrap NOTIFICATION-TYPE
		OBJECTS { trapCounter, gps3000p01v2Index, gps3000p01v2AntenaStat }
		STATUS current
		DESCRIPTION
			"Antenna connection status Trap"
		::= { gps3000p01v2Traps 29 }

		-- 1.3.6.1.4.1.10106.2.1.1.195703
		gps3000p01v3Traps OBJECT IDENTIFIER ::= { albalaTraps 195703 }

		-- 1.3.6.1.4.1.10106.2.1.1.195703.3
		gps3000p01v3HoldoverTrap NOTIFICATION-TYPE
		OBJECTS { trapCounter, gps3000p01v3Index, gps3000p01v3Holdover }
		STATUS current
		DESCRIPTION
			"Allows setting the module in the holdover mode Trap"
		::= { gps3000p01v3Traps 3 }

		-- 1.3.6.1.4.1.10106.2.1.1.195703.3
		gps3000p01v3HoldoverStatTrap NOTIFICATION-TYPE
		OBJECTS { trapCounter, gps3000p01v3Index, gps3000p01v3HoldoverStat }
		STATUS current
		DESCRIPTION
			"Indicates if the module is locked to GPS or to reference or it is in holdover mode Trap"
		::= { gps3000p01v3Traps 21 }

		-- 1.3.6.1.4.1.10106.2.1.1.195703.3
		gps3000p01v3RedundFailTrap NOTIFICATION-TYPE
		OBJECTS { trapCounter, gps3000p01v3Index, gps3000p01v3RedundFail }
		STATUS current
		DESCRIPTION
			"Indicates if there is any active module in the redundance system Trap"
		::= { gps3000p01v3Traps 23 }

		-- 1.3.6.1.4.1.10106.2.1.1.195703.3
		gps3000p01v3OutputsMutedTrap NOTIFICATION-TYPE
		OBJECTS { trapCounter, gps3000p01v3Index, gps3000p01v3OutputsMuted }
		STATUS current
		DESCRIPTION
			"Indicates f the module outputs are active Trap"
		::= { gps3000p01v3Traps 25 }

		-- 1.3.6.1.4.1.10106.2.1.1.195703.3
		gps3000p01v3AntenaStatTrap NOTIFICATION-TYPE
		OBJECTS { trapCounter, gps3000p01v3Index, gps3000p01v3AntenaStat }
		STATUS current
		DESCRIPTION
			"Antenna connection status Trap"
		::= { gps3000p01v3Traps 29 }

		-- 1.3.6.1.4.1.10106.2.1.1.195704
		gps3000p01v4Traps OBJECT IDENTIFIER ::= { albalaTraps 195704 }

		-- 1.3.6.1.4.1.10106.2.1.1.195704.3
		gps3000p01v4HoldoverTrap NOTIFICATION-TYPE
		OBJECTS { trapCounter, gps3000p01v4Index, gps3000p01v4Holdover }
		STATUS current
		DESCRIPTION
			"Allows setting the module in the holdover mode Trap"
		::= { gps3000p01v4Traps 3 }

		-- 1.3.6.1.4.1.10106.2.1.1.195704.3
		gps3000p01v4HoldoverStatTrap NOTIFICATION-TYPE
		OBJECTS { trapCounter, gps3000p01v4Index, gps3000p01v4HoldoverStat }
		STATUS current
		DESCRIPTION
			"Indicates if the module is locked to GPS or to reference or it is in holdover mode Trap"
		::= { gps3000p01v4Traps 21 }

		-- 1.3.6.1.4.1.10106.2.1.1.195704.3
		gps3000p01v4RedundFailTrap NOTIFICATION-TYPE
		OBJECTS { trapCounter, gps3000p01v4Index, gps3000p01v4RedundFail }
		STATUS current
		DESCRIPTION
			"Indicates if there is any active module in the redundance system Trap"
		::= { gps3000p01v4Traps 23 }

		-- 1.3.6.1.4.1.10106.2.1.1.195704.3
		gps3000p01v4OutputsMutedTrap NOTIFICATION-TYPE
		OBJECTS { trapCounter, gps3000p01v4Index, gps3000p01v4OutputsMuted }
		STATUS current
		DESCRIPTION
			"Indicates f the module outputs are active Trap"
		::= { gps3000p01v4Traps 25 }

		-- 1.3.6.1.4.1.10106.2.1.1.195704.3
		gps3000p01v4AntenaStatTrap NOTIFICATION-TYPE
		OBJECTS { trapCounter, gps3000p01v4Index, gps3000p01v4AntenaStat }
		STATUS current
		DESCRIPTION
			"Antenna connection status Trap"
		::= { gps3000p01v4Traps 29 }

		-- 1.3.6.1.4.1.10106.2.1.1.207201
		sdt3000p01v1Traps OBJECT IDENTIFIER ::= { albalaTraps 207201 }

		-- 1.3.6.1.4.1.10106.2.1.1.207201.3
		sdt3000p01v1NoSigATrap NOTIFICATION-TYPE
		OBJECTS { trapCounter, sdt3000p01v1Index, sdt3000p01v1NoSigA }
		STATUS current
		DESCRIPTION
			"Input signal status Trap"
		::= { sdt3000p01v1Traps 3 }

		-- 1.3.6.1.4.1.10106.2.1.1.207201.3
		sdt3000p01v1LaserFailATrap NOTIFICATION-TYPE
		OBJECTS { trapCounter, sdt3000p01v1Index, sdt3000p01v1LaserFailA }
		STATUS current
		DESCRIPTION
			"Laser status Trap"
		::= { sdt3000p01v1Traps 5 }

		-- 1.3.6.1.4.1.10106.2.1.1.207201.3
		sdt3000p01v1NoSigBTrap NOTIFICATION-TYPE
		OBJECTS { trapCounter, sdt3000p01v1Index, sdt3000p01v1NoSigB }
		STATUS current
		DESCRIPTION
			"Input signal status Trap"
		::= { sdt3000p01v1Traps 7 }

		-- 1.3.6.1.4.1.10106.2.1.1.207201.3
		sdt3000p01v1LaserFailBTrap NOTIFICATION-TYPE
		OBJECTS { trapCounter, sdt3000p01v1Index, sdt3000p01v1LaserFailB }
		STATUS current
		DESCRIPTION
			"Laser status Trap"
		::= { sdt3000p01v1Traps 9 }

		-- 1.3.6.1.4.1.10106.2.1.1.207301
		sdr3000p01v1Traps OBJECT IDENTIFIER ::= { albalaTraps 207301 }

		-- 1.3.6.1.4.1.10106.2.1.1.207301.3
		sdr3000p01v1NoSigATrap NOTIFICATION-TYPE
		OBJECTS { trapCounter, sdr3000p01v1Index, sdr3000p01v1NoSigA }
		STATUS current
		DESCRIPTION
			"Input signal status Trap"
		::= { sdr3000p01v1Traps 3 }

		-- 1.3.6.1.4.1.10106.2.1.1.207301.3
		sdr3000p01v1NoSigBTrap NOTIFICATION-TYPE
		OBJECTS { trapCounter, sdr3000p01v1Index, sdr3000p01v1NoSigB }
		STATUS current
		DESCRIPTION
			"Input signal status Trap"
		::= { sdr3000p01v1Traps 5 }

		-- 1.3.6.1.4.1.10106.2.1.1.211201
		dsw3000p05v1Traps OBJECT IDENTIFIER ::= { albalaTraps 211201 }

		-- 1.3.6.1.4.1.10106.2.1.1.211201.3
		dsw3000p05v1ModeTrap NOTIFICATION-TYPE
		OBJECTS { trapCounter, dsw3000p05v1Index, dsw3000p05v1Mode }
		STATUS current
		DESCRIPTION
			"Allows selecting the switching mode Trap"
		::= { dsw3000p05v1Traps 3 }

		-- 1.3.6.1.4.1.10106.2.1.1.211201.3
		dsw3000p05v1InputTrap NOTIFICATION-TYPE
		OBJECTS { trapCounter, dsw3000p05v1Index, dsw3000p05v1Input }
		STATUS current
		DESCRIPTION
			"Selected input Trap"
		::= { dsw3000p05v1Traps 7 }

		-- 1.3.6.1.4.1.10106.2.1.1.211201.3
		dsw3000p05v1MainFailTrap NOTIFICATION-TYPE
		OBJECTS { trapCounter, dsw3000p05v1Index, dsw3000p05v1MainFail }
		STATUS current
		DESCRIPTION
			"Main input status Trap"
		::= { dsw3000p05v1Traps 9 }

		-- 1.3.6.1.4.1.10106.2.1.1.211201.3
		dsw3000p05v1ExtMainFailTrap NOTIFICATION-TYPE
		OBJECTS { trapCounter, dsw3000p05v1Index, dsw3000p05v1ExtMainFail }
		STATUS current
		DESCRIPTION
			"Main external input fail status Trap"
		::= { dsw3000p05v1Traps 11 }

		-- 1.3.6.1.4.1.10106.2.1.1.211201.3
		dsw3000p05v1ResFailTrap NOTIFICATION-TYPE
		OBJECTS { trapCounter, dsw3000p05v1Index, dsw3000p05v1ResFail }
		STATUS current
		DESCRIPTION
			"Reserve input status Trap"
		::= { dsw3000p05v1Traps 13 }

		-- 1.3.6.1.4.1.10106.2.1.1.211201.3
		dsw3000p05v1ExtResFailTrap NOTIFICATION-TYPE
		OBJECTS { trapCounter, dsw3000p05v1Index, dsw3000p05v1ExtResFail }
		STATUS current
		DESCRIPTION
			"Reserve external input fail status Trap"
		::= { dsw3000p05v1Traps 15 }

		-- 1.3.6.1.4.1.10106.2.1.1.211201.3
		dsw3000p05v1AuxFailTrap NOTIFICATION-TYPE
		OBJECTS { trapCounter, dsw3000p05v1Index, dsw3000p05v1AuxFail }
		STATUS current
		DESCRIPTION
			"Auxiliar input status Trap"
		::= { dsw3000p05v1Traps 17 }

		-- 1.3.6.1.4.1.10106.2.1.1.211201.3
		dsw3000p05v1ExtAuxFailTrap NOTIFICATION-TYPE
		OBJECTS { trapCounter, dsw3000p05v1Index, dsw3000p05v1ExtAuxFail }
		STATUS current
		DESCRIPTION
			"Auxiliar external input fail status Trap"
		::= { dsw3000p05v1Traps 19 }

		-- 1.3.6.1.4.1.10106.2.1.1.213201
		gps3000p02v1Traps OBJECT IDENTIFIER ::= { albalaTraps 213201 }

		-- 1.3.6.1.4.1.10106.2.1.1.213201.3
		gps3000p02v1HoldoverTrap NOTIFICATION-TYPE
		OBJECTS { trapCounter, gps3000p02v1Index, gps3000p02v1Holdover }
		STATUS current
		DESCRIPTION
			"Allows setting the module in the holdover mode Trap"
		::= { gps3000p02v1Traps 3 }

		-- 1.3.6.1.4.1.10106.2.1.1.213201.3
		gps3000p02v1HoldoverStatTrap NOTIFICATION-TYPE
		OBJECTS { trapCounter, gps3000p02v1Index, gps3000p02v1HoldoverStat }
		STATUS current
		DESCRIPTION
			"Indicates if the module is locked to GPS or to reference or it is in holdover mode Trap"
		::= { gps3000p02v1Traps 21 }

		-- 1.3.6.1.4.1.10106.2.1.1.213201.3
		gps3000p02v1RedundFailTrap NOTIFICATION-TYPE
		OBJECTS { trapCounter, gps3000p02v1Index, gps3000p02v1RedundFail }
		STATUS current
		DESCRIPTION
			"Indicates if there is any active module in the redundance system Trap"
		::= { gps3000p02v1Traps 23 }

		-- 1.3.6.1.4.1.10106.2.1.1.213201.3
		gps3000p02v1OutputsMutedTrap NOTIFICATION-TYPE
		OBJECTS { trapCounter, gps3000p02v1Index, gps3000p02v1OutputsMuted }
		STATUS current
		DESCRIPTION
			"Indicates f the module outputs are active Trap"
		::= { gps3000p02v1Traps 25 }

		-- 1.3.6.1.4.1.10106.2.1.1.213201.3
		gps3000p02v1AntenaStatTrap NOTIFICATION-TYPE
		OBJECTS { trapCounter, gps3000p02v1Index, gps3000p02v1AntenaStat }
		STATUS current
		DESCRIPTION
			"Antenna connection status Trap"
		::= { gps3000p02v1Traps 29 }

		-- 1.3.6.1.4.1.10106.2.1.1.213202
		gps3000p02v2Traps OBJECT IDENTIFIER ::= { albalaTraps 213202 }

		-- 1.3.6.1.4.1.10106.2.1.1.213202.3
		gps3000p02v2HoldoverTrap NOTIFICATION-TYPE
		OBJECTS { trapCounter, gps3000p02v2Index, gps3000p02v2Holdover }
		STATUS current
		DESCRIPTION
			"Allows setting the module in the holdover mode Trap"
		::= { gps3000p02v2Traps 3 }

		-- 1.3.6.1.4.1.10106.2.1.1.213202.3
		gps3000p02v2HoldoverStatTrap NOTIFICATION-TYPE
		OBJECTS { trapCounter, gps3000p02v2Index, gps3000p02v2HoldoverStat }
		STATUS current
		DESCRIPTION
			"Indicates if the module is locked to GPS or to reference or it is in holdover mode Trap"
		::= { gps3000p02v2Traps 21 }

		-- 1.3.6.1.4.1.10106.2.1.1.213202.3
		gps3000p02v2RedundFailTrap NOTIFICATION-TYPE
		OBJECTS { trapCounter, gps3000p02v2Index, gps3000p02v2RedundFail }
		STATUS current
		DESCRIPTION
			"Indicates if there is any active module in the redundance system Trap"
		::= { gps3000p02v2Traps 23 }

		-- 1.3.6.1.4.1.10106.2.1.1.213202.3
		gps3000p02v2OutputsMutedTrap NOTIFICATION-TYPE
		OBJECTS { trapCounter, gps3000p02v2Index, gps3000p02v2OutputsMuted }
		STATUS current
		DESCRIPTION
			"Indicates f the module outputs are active Trap"
		::= { gps3000p02v2Traps 25 }

		-- 1.3.6.1.4.1.10106.2.1.1.213202.3
		gps3000p02v2AntenaStatTrap NOTIFICATION-TYPE
		OBJECTS { trapCounter, gps3000p02v2Index, gps3000p02v2AntenaStat }
		STATUS current
		DESCRIPTION
			"Antenna connection status Trap"
		::= { gps3000p02v2Traps 29 }

		-- 1.3.6.1.4.1.10106.2.1.1.213203
		gps3000p02v3Traps OBJECT IDENTIFIER ::= { albalaTraps 213203 }

		-- 1.3.6.1.4.1.10106.2.1.1.213203.3
		gps3000p02v3HoldoverTrap NOTIFICATION-TYPE
		OBJECTS { trapCounter, gps3000p02v3Index, gps3000p02v3Holdover }
		STATUS current
		DESCRIPTION
			"Allows setting the module in the holdover mode Trap"
		::= { gps3000p02v3Traps 3 }

		-- 1.3.6.1.4.1.10106.2.1.1.213203.3
		gps3000p02v3HoldoverStatTrap NOTIFICATION-TYPE
		OBJECTS { trapCounter, gps3000p02v3Index, gps3000p02v3HoldoverStat }
		STATUS current
		DESCRIPTION
			"Indicates if the module is locked to GPS or to reference or it is in holdover mode Trap"
		::= { gps3000p02v3Traps 21 }

		-- 1.3.6.1.4.1.10106.2.1.1.213203.3
		gps3000p02v3RedundFailTrap NOTIFICATION-TYPE
		OBJECTS { trapCounter, gps3000p02v3Index, gps3000p02v3RedundFail }
		STATUS current
		DESCRIPTION
			"Indicates if there is any active module in the redundance system Trap"
		::= { gps3000p02v3Traps 23 }

		-- 1.3.6.1.4.1.10106.2.1.1.213203.3
		gps3000p02v3OutputsMutedTrap NOTIFICATION-TYPE
		OBJECTS { trapCounter, gps3000p02v3Index, gps3000p02v3OutputsMuted }
		STATUS current
		DESCRIPTION
			"Indicates f the module outputs are active Trap"
		::= { gps3000p02v3Traps 25 }

		-- 1.3.6.1.4.1.10106.2.1.1.213203.3
		gps3000p02v3AntenaStatTrap NOTIFICATION-TYPE
		OBJECTS { trapCounter, gps3000p02v3Index, gps3000p02v3AntenaStat }
		STATUS current
		DESCRIPTION
			"Antenna connection status Trap"
		::= { gps3000p02v3Traps 29 }

		-- 1.3.6.1.4.1.10106.2.1.1.213204
		gps3000p02v4Traps OBJECT IDENTIFIER ::= { albalaTraps 213204 }

		-- 1.3.6.1.4.1.10106.2.1.1.213204.3
		gps3000p02v4HoldoverTrap NOTIFICATION-TYPE
		OBJECTS { trapCounter, gps3000p02v4Index, gps3000p02v4Holdover }
		STATUS current
		DESCRIPTION
			"Allows setting the module in the holdover mode Trap"
		::= { gps3000p02v4Traps 3 }

		-- 1.3.6.1.4.1.10106.2.1.1.213204.3
		gps3000p02v4HoldoverStatTrap NOTIFICATION-TYPE
		OBJECTS { trapCounter, gps3000p02v4Index, gps3000p02v4HoldoverStat }
		STATUS current
		DESCRIPTION
			"Indicates if the module is locked to GPS or to reference or it is in holdover mode Trap"
		::= { gps3000p02v4Traps 21 }

		-- 1.3.6.1.4.1.10106.2.1.1.213204.3
		gps3000p02v4RedundFailTrap NOTIFICATION-TYPE
		OBJECTS { trapCounter, gps3000p02v4Index, gps3000p02v4RedundFail }
		STATUS current
		DESCRIPTION
			"Indicates if there is any active module in the redundance system Trap"
		::= { gps3000p02v4Traps 23 }

		-- 1.3.6.1.4.1.10106.2.1.1.213204.3
		gps3000p02v4OutputsMutedTrap NOTIFICATION-TYPE
		OBJECTS { trapCounter, gps3000p02v4Index, gps3000p02v4OutputsMuted }
		STATUS current
		DESCRIPTION
			"Indicates f the module outputs are active Trap"
		::= { gps3000p02v4Traps 25 }

		-- 1.3.6.1.4.1.10106.2.1.1.213204.3
		gps3000p02v4AntenaStatTrap NOTIFICATION-TYPE
		OBJECTS { trapCounter, gps3000p02v4Index, gps3000p02v4AntenaStat }
		STATUS current
		DESCRIPTION
			"Antenna connection status Trap"
		::= { gps3000p02v4Traps 29 }

		-- 1.3.6.1.4.1.10106.2.1.1.215401
		pds3001p01v1Traps OBJECT IDENTIFIER ::= { albalaTraps 215401 }

		-- 1.3.6.1.4.1.10106.2.1.1.215401.3
		pds3001p01v1UnlockTrap NOTIFICATION-TYPE
		OBJECTS { trapCounter, pds3001p01v1Index, pds3001p01v1Unlock }
		STATUS current
		DESCRIPTION
			"Indicates signal unlock fail Trap"
		::= { pds3001p01v1Traps 33 }

		-- 1.3.6.1.4.1.10106.2.1.1.215401.3
		pds3001p01v1BlackTrap NOTIFICATION-TYPE
		OBJECTS { trapCounter, pds3001p01v1Index, pds3001p01v1Black }
		STATUS current
		DESCRIPTION
			"Indicates black pattern instantaneous fail Trap"
		::= { pds3001p01v1Traps 35 }

		-- 1.3.6.1.4.1.10106.2.1.1.215401.3
		pds3001p01v1FreezeTrap NOTIFICATION-TYPE
		OBJECTS { trapCounter, pds3001p01v1Index, pds3001p01v1Freeze }
		STATUS current
		DESCRIPTION
			"Indicates freeze image instantaneous fail Trap"
		::= { pds3001p01v1Traps 37 }

		-- 1.3.6.1.4.1.10106.2.1.1.215401.3
		pds3001p01v1UnlockTTrap NOTIFICATION-TYPE
		OBJECTS { trapCounter, pds3001p01v1Index, pds3001p01v1UnlockT }
		STATUS current
		DESCRIPTION
			"Indicates unlock filtered fail Trap"
		::= { pds3001p01v1Traps 39 }

		-- 1.3.6.1.4.1.10106.2.1.1.215401.3
		pds3001p01v1BlackTTrap NOTIFICATION-TYPE
		OBJECTS { trapCounter, pds3001p01v1Index, pds3001p01v1BlackT }
		STATUS current
		DESCRIPTION
			"Indicates black pattern filtered fail Trap"
		::= { pds3001p01v1Traps 41 }

		-- 1.3.6.1.4.1.10106.2.1.1.215401.3
		pds3001p01v1FreezeTTrap NOTIFICATION-TYPE
		OBJECTS { trapCounter, pds3001p01v1Index, pds3001p01v1FreezeT }
		STATUS current
		DESCRIPTION
			"Indicates freeze image filtered fail Trap"
		::= { pds3001p01v1Traps 43 }

		-- 1.3.6.1.4.1.10106.2.1.1.215401.3
		pds3001p01v1OverloadTrap NOTIFICATION-TYPE
		OBJECTS { trapCounter, pds3001p01v1Index, pds3001p01v1Overload }
		STATUS current
		DESCRIPTION
			"Indicates the that the input level is too high Trap"
		::= { pds3001p01v1Traps 45 }

		-- 1.3.6.1.4.1.10106.2.1.1.216401
		gps3000p03v1Traps OBJECT IDENTIFIER ::= { albalaTraps 216401 }

		-- 1.3.6.1.4.1.10106.2.1.1.216401.3
		gps3000p03v1HoldoverTrap NOTIFICATION-TYPE
		OBJECTS { trapCounter, gps3000p03v1Index, gps3000p03v1Holdover }
		STATUS current
		DESCRIPTION
			"Allows setting the module in the holdover mode Trap"
		::= { gps3000p03v1Traps 3 }

		-- 1.3.6.1.4.1.10106.2.1.1.216401.3
		gps3000p03v1HoldoverStatTrap NOTIFICATION-TYPE
		OBJECTS { trapCounter, gps3000p03v1Index, gps3000p03v1HoldoverStat }
		STATUS current
		DESCRIPTION
			"Indicates if the module is locked to GPS or to reference or it is in holdover mode Trap"
		::= { gps3000p03v1Traps 21 }

		-- 1.3.6.1.4.1.10106.2.1.1.216401.3
		gps3000p03v1RedundFailTrap NOTIFICATION-TYPE
		OBJECTS { trapCounter, gps3000p03v1Index, gps3000p03v1RedundFail }
		STATUS current
		DESCRIPTION
			"Indicates if there is any active module in the redundance system Trap"
		::= { gps3000p03v1Traps 23 }

		-- 1.3.6.1.4.1.10106.2.1.1.216401.3
		gps3000p03v1OutputsMutedTrap NOTIFICATION-TYPE
		OBJECTS { trapCounter, gps3000p03v1Index, gps3000p03v1OutputsMuted }
		STATUS current
		DESCRIPTION
			"Indicates f the module outputs are active Trap"
		::= { gps3000p03v1Traps 25 }

		-- 1.3.6.1.4.1.10106.2.1.1.216401.3
		gps3000p03v1AntenaStatTrap NOTIFICATION-TYPE
		OBJECTS { trapCounter, gps3000p03v1Index, gps3000p03v1AntenaStat }
		STATUS current
		DESCRIPTION
			"Antenna connection status Trap"
		::= { gps3000p03v1Traps 29 }

		-- 1.3.6.1.4.1.10106.2.1.1.216402
		gps3000p03v2Traps OBJECT IDENTIFIER ::= { albalaTraps 216402 }

		-- 1.3.6.1.4.1.10106.2.1.1.216402.3
		gps3000p03v2HoldoverTrap NOTIFICATION-TYPE
		OBJECTS { trapCounter, gps3000p03v2Index, gps3000p03v2Holdover }
		STATUS current
		DESCRIPTION
			"Allows setting the module in the holdover mode Trap"
		::= { gps3000p03v2Traps 3 }

		-- 1.3.6.1.4.1.10106.2.1.1.216402.3
		gps3000p03v2HoldoverStatTrap NOTIFICATION-TYPE
		OBJECTS { trapCounter, gps3000p03v2Index, gps3000p03v2HoldoverStat }
		STATUS current
		DESCRIPTION
			"Indicates if the module is locked to GPS or to reference or it is in holdover mode Trap"
		::= { gps3000p03v2Traps 21 }

		-- 1.3.6.1.4.1.10106.2.1.1.216402.3
		gps3000p03v2RedundFailTrap NOTIFICATION-TYPE
		OBJECTS { trapCounter, gps3000p03v2Index, gps3000p03v2RedundFail }
		STATUS current
		DESCRIPTION
			"Indicates if there is any active module in the redundance system Trap"
		::= { gps3000p03v2Traps 23 }

		-- 1.3.6.1.4.1.10106.2.1.1.216402.3
		gps3000p03v2OutputsMutedTrap NOTIFICATION-TYPE
		OBJECTS { trapCounter, gps3000p03v2Index, gps3000p03v2OutputsMuted }
		STATUS current
		DESCRIPTION
			"Indicates f the module outputs are active Trap"
		::= { gps3000p03v2Traps 25 }

		-- 1.3.6.1.4.1.10106.2.1.1.216402.3
		gps3000p03v2AntenaStatTrap NOTIFICATION-TYPE
		OBJECTS { trapCounter, gps3000p03v2Index, gps3000p03v2AntenaStat }
		STATUS current
		DESCRIPTION
			"Antenna connection status Trap"
		::= { gps3000p03v2Traps 29 }

		-- 1.3.6.1.4.1.10106.2.1.1.216403
		gps3000p03v3Traps OBJECT IDENTIFIER ::= { albalaTraps 216403 }

		-- 1.3.6.1.4.1.10106.2.1.1.216403.3
		gps3000p03v3HoldoverTrap NOTIFICATION-TYPE
		OBJECTS { trapCounter, gps3000p03v3Index, gps3000p03v3Holdover }
		STATUS current
		DESCRIPTION
			"Allows setting the module in the holdover mode Trap"
		::= { gps3000p03v3Traps 3 }

		-- 1.3.6.1.4.1.10106.2.1.1.216403.3
		gps3000p03v3HoldoverStatTrap NOTIFICATION-TYPE
		OBJECTS { trapCounter, gps3000p03v3Index, gps3000p03v3HoldoverStat }
		STATUS current
		DESCRIPTION
			"Indicates if the module is locked to GPS or to reference or it is in holdover mode Trap"
		::= { gps3000p03v3Traps 21 }

		-- 1.3.6.1.4.1.10106.2.1.1.216403.3
		gps3000p03v3RedundFailTrap NOTIFICATION-TYPE
		OBJECTS { trapCounter, gps3000p03v3Index, gps3000p03v3RedundFail }
		STATUS current
		DESCRIPTION
			"Indicates if there is any active module in the redundance system Trap"
		::= { gps3000p03v3Traps 23 }

		-- 1.3.6.1.4.1.10106.2.1.1.216403.3
		gps3000p03v3OutputsMutedTrap NOTIFICATION-TYPE
		OBJECTS { trapCounter, gps3000p03v3Index, gps3000p03v3OutputsMuted }
		STATUS current
		DESCRIPTION
			"Indicates f the module outputs are active Trap"
		::= { gps3000p03v3Traps 25 }

		-- 1.3.6.1.4.1.10106.2.1.1.216403.3
		gps3000p03v3AntenaStatTrap NOTIFICATION-TYPE
		OBJECTS { trapCounter, gps3000p03v3Index, gps3000p03v3AntenaStat }
		STATUS current
		DESCRIPTION
			"Antenna connection status Trap"
		::= { gps3000p03v3Traps 29 }

		-- 1.3.6.1.4.1.10106.2.1.1.216404
		gps3000p03v4Traps OBJECT IDENTIFIER ::= { albalaTraps 216404 }

		-- 1.3.6.1.4.1.10106.2.1.1.216404.3
		gps3000p03v4HoldoverTrap NOTIFICATION-TYPE
		OBJECTS { trapCounter, gps3000p03v4Index, gps3000p03v4Holdover }
		STATUS current
		DESCRIPTION
			"Allows setting the module in the holdover mode Trap"
		::= { gps3000p03v4Traps 3 }

		-- 1.3.6.1.4.1.10106.2.1.1.216404.3
		gps3000p03v4HoldoverStatTrap NOTIFICATION-TYPE
		OBJECTS { trapCounter, gps3000p03v4Index, gps3000p03v4HoldoverStat }
		STATUS current
		DESCRIPTION
			"Indicates if the module is locked to GPS or to reference or it is in holdover mode Trap"
		::= { gps3000p03v4Traps 21 }

		-- 1.3.6.1.4.1.10106.2.1.1.216404.3
		gps3000p03v4RedundFailTrap NOTIFICATION-TYPE
		OBJECTS { trapCounter, gps3000p03v4Index, gps3000p03v4RedundFail }
		STATUS current
		DESCRIPTION
			"Indicates if there is any active module in the redundance system Trap"
		::= { gps3000p03v4Traps 23 }

		-- 1.3.6.1.4.1.10106.2.1.1.216404.3
		gps3000p03v4OutputsMutedTrap NOTIFICATION-TYPE
		OBJECTS { trapCounter, gps3000p03v4Index, gps3000p03v4OutputsMuted }
		STATUS current
		DESCRIPTION
			"Indicates f the module outputs are active Trap"
		::= { gps3000p03v4Traps 25 }

		-- 1.3.6.1.4.1.10106.2.1.1.216404.3
		gps3000p03v4AntenaStatTrap NOTIFICATION-TYPE
		OBJECTS { trapCounter, gps3000p03v4Index, gps3000p03v4AntenaStat }
		STATUS current
		DESCRIPTION
			"Antenna connection status Trap"
		::= { gps3000p03v4Traps 29 }

		-- 1.3.6.1.4.1.10106.2.1.1.224701
		frs3004c02v1Traps OBJECT IDENTIFIER ::= { albalaTraps 224701 }

		-- 1.3.6.1.4.1.10106.2.1.1.224701.3
		frs3004c02v1NoRefTrap NOTIFICATION-TYPE
		OBJECTS { trapCounter, frs3004c02v1Index, frs3004c02v1NoRef }
		STATUS current
		DESCRIPTION
			"Indicates reference signal fail Trap"
		::= { frs3004c02v1Traps 51 }

		-- 1.3.6.1.4.1.10106.2.1.1.224701.3
		frs3004c02v1RefUnlockTrap NOTIFICATION-TYPE
		OBJECTS { trapCounter, frs3004c02v1Index, frs3004c02v1RefUnlock }
		STATUS current
		DESCRIPTION
			"Indicates reference signal unlock fail Trap"
		::= { frs3004c02v1Traps 53 }

		-- 1.3.6.1.4.1.10106.2.1.1.224701.3
		frs3004c02v1NoSig1Trap NOTIFICATION-TYPE
		OBJECTS { trapCounter, frs3004c02v1Index, frs3004c02v1NoSig1 }
		STATUS current
		DESCRIPTION
			"Indicates SDI signal fail Trap"
		::= { frs3004c02v1Traps 59 }

		-- 1.3.6.1.4.1.10106.2.1.1.224701.3
		frs3004c02v1NoSig2Trap NOTIFICATION-TYPE
		OBJECTS { trapCounter, frs3004c02v1Index, frs3004c02v1NoSig2 }
		STATUS current
		DESCRIPTION
			"Indicates SDI signal fail Trap"
		::= { frs3004c02v1Traps 61 }

		-- 1.3.6.1.4.1.10106.2.1.1.224701.3
		frs3004c02v1NoSig3Trap NOTIFICATION-TYPE
		OBJECTS { trapCounter, frs3004c02v1Index, frs3004c02v1NoSig3 }
		STATUS current
		DESCRIPTION
			"Indicates SDI signal fail Trap"
		::= { frs3004c02v1Traps 63 }

		-- 1.3.6.1.4.1.10106.2.1.1.224701.3
		frs3004c02v1NoSig4Trap NOTIFICATION-TYPE
		OBJECTS { trapCounter, frs3004c02v1Index, frs3004c02v1NoSig4 }
		STATUS current
		DESCRIPTION
			"Indicates SDI signal fail Trap"
		::= { frs3004c02v1Traps 65 }

		-- 1.3.6.1.4.1.10106.2.1.1.229601
		dvd3001p01v1Traps OBJECT IDENTIFIER ::= { albalaTraps 229601 }

		-- 1.3.6.1.4.1.10106.2.1.1.229601.3
		dvd3001p01v1NoSigATrap NOTIFICATION-TYPE
		OBJECTS { trapCounter, dvd3001p01v1Index, dvd3001p01v1NoSigA }
		STATUS current
		DESCRIPTION
			"Input signal status Trap"
		::= { dvd3001p01v1Traps 3 }

		-- 1.3.6.1.4.1.10106.2.1.1.229601.3
		dvd3001p01v1NoSigBTrap NOTIFICATION-TYPE
		OBJECTS { trapCounter, dvd3001p01v1Index, dvd3001p01v1NoSigB }
		STATUS current
		DESCRIPTION
			"Input signal status Trap"
		::= { dvd3001p01v1Traps 7 }

		-- 1.3.6.1.4.1.10106.2.1.1.232401
		frs3004c01v1Traps OBJECT IDENTIFIER ::= { albalaTraps 232401 }

		-- 1.3.6.1.4.1.10106.2.1.1.232401.3
		frs3004c01v1NoRefTrap NOTIFICATION-TYPE
		OBJECTS { trapCounter, frs3004c01v1Index, frs3004c01v1NoRef }
		STATUS current
		DESCRIPTION
			"Indicates reference signal fail Trap"
		::= { frs3004c01v1Traps 51 }

		-- 1.3.6.1.4.1.10106.2.1.1.232401.3
		frs3004c01v1RefUnlockTrap NOTIFICATION-TYPE
		OBJECTS { trapCounter, frs3004c01v1Index, frs3004c01v1RefUnlock }
		STATUS current
		DESCRIPTION
			"Indicates reference signal unlock fail Trap"
		::= { frs3004c01v1Traps 53 }

		-- 1.3.6.1.4.1.10106.2.1.1.232401.3
		frs3004c01v1NoSig1Trap NOTIFICATION-TYPE
		OBJECTS { trapCounter, frs3004c01v1Index, frs3004c01v1NoSig1 }
		STATUS current
		DESCRIPTION
			"Indicates SDI signal fail Trap"
		::= { frs3004c01v1Traps 59 }

		-- 1.3.6.1.4.1.10106.2.1.1.232401.3
		frs3004c01v1NoSig2Trap NOTIFICATION-TYPE
		OBJECTS { trapCounter, frs3004c01v1Index, frs3004c01v1NoSig2 }
		STATUS current
		DESCRIPTION
			"Indicates SDI signal fail Trap"
		::= { frs3004c01v1Traps 61 }

		-- 1.3.6.1.4.1.10106.2.1.1.232401.3
		frs3004c01v1NoSig3Trap NOTIFICATION-TYPE
		OBJECTS { trapCounter, frs3004c01v1Index, frs3004c01v1NoSig3 }
		STATUS current
		DESCRIPTION
			"Indicates SDI signal fail Trap"
		::= { frs3004c01v1Traps 63 }

		-- 1.3.6.1.4.1.10106.2.1.1.232401.3
		frs3004c01v1NoSig4Trap NOTIFICATION-TYPE
		OBJECTS { trapCounter, frs3004c01v1Index, frs3004c01v1NoSig4 }
		STATUS current
		DESCRIPTION
			"Indicates SDI signal fail Trap"
		::= { frs3004c01v1Traps 65 }

		-- 1.3.6.1.4.1.10106.2.1.1.233401
		dvd3001c02v1Traps OBJECT IDENTIFIER ::= { albalaTraps 233401 }

		-- 1.3.6.1.4.1.10106.2.1.1.233401.3
		dvd3001c02v1NoSigATrap NOTIFICATION-TYPE
		OBJECTS { trapCounter, dvd3001c02v1Index, dvd3001c02v1NoSigA }
		STATUS current
		DESCRIPTION
			"Input signal status Trap"
		::= { dvd3001c02v1Traps 3 }

		-- 1.3.6.1.4.1.10106.2.1.1.233401.3
		dvd3001c02v1NoSigBTrap NOTIFICATION-TYPE
		OBJECTS { trapCounter, dvd3001c02v1Index, dvd3001c02v1NoSigB }
		STATUS current
		DESCRIPTION
			"Input signal status Trap"
		::= { dvd3001c02v1Traps 7 }

		-- 1.3.6.1.4.1.10106.2.1.1.233501
		dvd3001c03v1Traps OBJECT IDENTIFIER ::= { albalaTraps 233501 }

		-- 1.3.6.1.4.1.10106.2.1.1.233501.3
		dvd3001c03v1NoSigATrap NOTIFICATION-TYPE
		OBJECTS { trapCounter, dvd3001c03v1Index, dvd3001c03v1NoSigA }
		STATUS current
		DESCRIPTION
			"Input signal status Trap"
		::= { dvd3001c03v1Traps 3 }

		-- 1.3.6.1.4.1.10106.2.1.1.233501.3
		dvd3001c03v1NoSigBTrap NOTIFICATION-TYPE
		OBJECTS { trapCounter, dvd3001c03v1Index, dvd3001c03v1NoSigB }
		STATUS current
		DESCRIPTION
			"Input signal status Trap"
		::= { dvd3001c03v1Traps 7 }

		-- 1.3.6.1.4.1.10106.2.1.1.234101
		dvd3001c04v1Traps OBJECT IDENTIFIER ::= { albalaTraps 234101 }

		-- 1.3.6.1.4.1.10106.2.1.1.234101.3
		dvd3001c04v1NoSigATrap NOTIFICATION-TYPE
		OBJECTS { trapCounter, dvd3001c04v1Index, dvd3001c04v1NoSigA }
		STATUS current
		DESCRIPTION
			"Input signal status Trap"
		::= { dvd3001c04v1Traps 3 }

		-- 1.3.6.1.4.1.10106.2.1.1.234201
		dvd3001c05v1Traps OBJECT IDENTIFIER ::= { albalaTraps 234201 }

		-- 1.3.6.1.4.1.10106.2.1.1.234201.3
		dvd3001c05v1NoSigATrap NOTIFICATION-TYPE
		OBJECTS { trapCounter, dvd3001c05v1Index, dvd3001c05v1NoSigA }
		STATUS current
		DESCRIPTION
			"Input signal status Trap"
		::= { dvd3001c05v1Traps 3 }

		-- 1.3.6.1.4.1.10106.2.1.1.238701
		sdr3000p02v1Traps OBJECT IDENTIFIER ::= { albalaTraps 238701 }

		-- 1.3.6.1.4.1.10106.2.1.1.238701.3
		sdr3000p02v1NoSigATrap NOTIFICATION-TYPE
		OBJECTS { trapCounter, sdr3000p02v1Index, sdr3000p02v1NoSigA }
		STATUS current
		DESCRIPTION
			"Input signal status Trap"
		::= { sdr3000p02v1Traps 3 }

		-- 1.3.6.1.4.1.10106.2.1.1.238701.3
		sdr3000p02v1NoSigBTrap NOTIFICATION-TYPE
		OBJECTS { trapCounter, sdr3000p02v1Index, sdr3000p02v1NoSigB }
		STATUS current
		DESCRIPTION
			"Input signal status Trap"
		::= { sdr3000p02v1Traps 5 }

		-- 1.3.6.1.4.1.10106.2.1.1.241501
		asw3000c01v1Traps OBJECT IDENTIFIER ::= { albalaTraps 241501 }

		-- 1.3.6.1.4.1.10106.2.1.1.241501.3
		asw3000c01v1ModeTrap NOTIFICATION-TYPE
		OBJECTS { trapCounter, asw3000c01v1Index, asw3000c01v1Mode }
		STATUS current
		DESCRIPTION
			"Allows selecting the switching mode Trap"
		::= { asw3000c01v1Traps 3 }

		-- 1.3.6.1.4.1.10106.2.1.1.241501.3
		asw3000c01v1InputTrap NOTIFICATION-TYPE
		OBJECTS { trapCounter, asw3000c01v1Index, asw3000c01v1Input }
		STATUS current
		DESCRIPTION
			"Selected input Trap"
		::= { asw3000c01v1Traps 7 }

		-- 1.3.6.1.4.1.10106.2.1.1.241501.3
		asw3000c01v1MainGlobalFailTrap NOTIFICATION-TYPE
		OBJECTS { trapCounter, asw3000c01v1Index, asw3000c01v1MainGlobalFail }
		STATUS current
		DESCRIPTION
			"Main input global (any kind) fail status Trap"
		::= { asw3000c01v1Traps 43 }

		-- 1.3.6.1.4.1.10106.2.1.1.241501.3
		asw3000c01v1ResGlobalFailTrap NOTIFICATION-TYPE
		OBJECTS { trapCounter, asw3000c01v1Index, asw3000c01v1ResGlobalFail }
		STATUS current
		DESCRIPTION
			"Reserve input global (any kind) fail status Trap"
		::= { asw3000c01v1Traps 47 }

		-- 1.3.6.1.4.1.10106.2.1.1.241501.3
		asw3000c01v1MainGpiFailTrap NOTIFICATION-TYPE
		OBJECTS { trapCounter, asw3000c01v1Index, asw3000c01v1MainGpiFail }
		STATUS current
		DESCRIPTION
			"Main external fail (GPI) status Trap"
		::= { asw3000c01v1Traps 49 }

		-- 1.3.6.1.4.1.10106.2.1.1.241501.3
		asw3000c01v1MainPresFailTrap NOTIFICATION-TYPE
		OBJECTS { trapCounter, asw3000c01v1Index, asw3000c01v1MainPresFail }
		STATUS current
		DESCRIPTION
			"Main signal presence status Trap"
		::= { asw3000c01v1Traps 51 }

		-- 1.3.6.1.4.1.10106.2.1.1.241501.3
		asw3000c01v1MainSyncLFailTrap NOTIFICATION-TYPE
		OBJECTS { trapCounter, asw3000c01v1Index, asw3000c01v1MainSyncLFail }
		STATUS current
		DESCRIPTION
			"Main TS sync status Trap"
		::= { asw3000c01v1Traps 53 }

		-- 1.3.6.1.4.1.10106.2.1.1.241501.3
		asw3000c01v1MainSyncBFailTrap NOTIFICATION-TYPE
		OBJECTS { trapCounter, asw3000c01v1Index, asw3000c01v1MainSyncBFail }
		STATUS current
		DESCRIPTION
			"Main sync byte presence status Trap"
		::= { asw3000c01v1Traps 55 }

		-- 1.3.6.1.4.1.10106.2.1.1.241501.3
		asw3000c01v1MainPatErFailTrap NOTIFICATION-TYPE
		OBJECTS { trapCounter, asw3000c01v1Index, asw3000c01v1MainPatErFail }
		STATUS current
		DESCRIPTION
			"Main PAT status Trap"
		::= { asw3000c01v1Traps 57 }

		-- 1.3.6.1.4.1.10106.2.1.1.241501.3
		asw3000c01v1MainPatCcFailTrap NOTIFICATION-TYPE
		OBJECTS { trapCounter, asw3000c01v1Index, asw3000c01v1MainPatCcFail }
		STATUS current
		DESCRIPTION
			"Main PAT continuity counter status Trap"
		::= { asw3000c01v1Traps 59 }

		-- 1.3.6.1.4.1.10106.2.1.1.241501.3
		asw3000c01v1MainTraffFailTrap NOTIFICATION-TYPE
		OBJECTS { trapCounter, asw3000c01v1Index, asw3000c01v1MainTraffFail }
		STATUS current
		DESCRIPTION
			"Main bitrate status Trap"
		::= { asw3000c01v1Traps 61 }

		-- 1.3.6.1.4.1.10106.2.1.1.241501.3
		asw3000c01v1MainNullPFailTrap NOTIFICATION-TYPE
		OBJECTS { trapCounter, asw3000c01v1Index, asw3000c01v1MainNullPFail }
		STATUS current
		DESCRIPTION
			"Main null packet rate status Trap"
		::= { asw3000c01v1Traps 63 }

		-- 1.3.6.1.4.1.10106.2.1.1.241501.3
		asw3000c01v1ResGpiFailTrap NOTIFICATION-TYPE
		OBJECTS { trapCounter, asw3000c01v1Index, asw3000c01v1ResGpiFail }
		STATUS current
		DESCRIPTION
			"Main external fail (GPI) status Trap"
		::= { asw3000c01v1Traps 65 }

		-- 1.3.6.1.4.1.10106.2.1.1.241501.3
		asw3000c01v1ResPresFailTrap NOTIFICATION-TYPE
		OBJECTS { trapCounter, asw3000c01v1Index, asw3000c01v1ResPresFail }
		STATUS current
		DESCRIPTION
			"Main signal presence status Trap"
		::= { asw3000c01v1Traps 67 }

		-- 1.3.6.1.4.1.10106.2.1.1.241501.3
		asw3000c01v1ResSyncLFailTrap NOTIFICATION-TYPE
		OBJECTS { trapCounter, asw3000c01v1Index, asw3000c01v1ResSyncLFail }
		STATUS current
		DESCRIPTION
			"Main TS sync status Trap"
		::= { asw3000c01v1Traps 69 }

		-- 1.3.6.1.4.1.10106.2.1.1.241501.3
		asw3000c01v1ResSyncBFailTrap NOTIFICATION-TYPE
		OBJECTS { trapCounter, asw3000c01v1Index, asw3000c01v1ResSyncBFail }
		STATUS current
		DESCRIPTION
			"Main sync byte presence status Trap"
		::= { asw3000c01v1Traps 71 }

		-- 1.3.6.1.4.1.10106.2.1.1.241501.3
		asw3000c01v1ResPatErFailTrap NOTIFICATION-TYPE
		OBJECTS { trapCounter, asw3000c01v1Index, asw3000c01v1ResPatErFail }
		STATUS current
		DESCRIPTION
			"Main PAT status Trap"
		::= { asw3000c01v1Traps 73 }

		-- 1.3.6.1.4.1.10106.2.1.1.241501.3
		asw3000c01v1ResPatCcFailTrap NOTIFICATION-TYPE
		OBJECTS { trapCounter, asw3000c01v1Index, asw3000c01v1ResPatCcFail }
		STATUS current
		DESCRIPTION
			"Main PAT continuity counter status Trap"
		::= { asw3000c01v1Traps 75 }

		-- 1.3.6.1.4.1.10106.2.1.1.241501.3
		asw3000c01v1ResTraffFailTrap NOTIFICATION-TYPE
		OBJECTS { trapCounter, asw3000c01v1Index, asw3000c01v1ResTraffFail }
		STATUS current
		DESCRIPTION
			"Main bitrate status Trap"
		::= { asw3000c01v1Traps 77 }

		-- 1.3.6.1.4.1.10106.2.1.1.241501.3
		asw3000c01v1ResNullPFailTrap NOTIFICATION-TYPE
		OBJECTS { trapCounter, asw3000c01v1Index, asw3000c01v1ResNullPFail }
		STATUS current
		DESCRIPTION
			"Main null packet rate status Trap"
		::= { asw3000c01v1Traps 79 }

		-- 1.3.6.1.4.1.10106.2.1.1.245601
		adl3000c01v1Traps OBJECT IDENTIFIER ::= { albalaTraps 245601 }

		-- 1.3.6.1.4.1.10106.2.1.1.245601.3
		adl3000c01v1GlobalFailTrap NOTIFICATION-TYPE
		OBJECTS { trapCounter, adl3000c01v1Index, adl3000c01v1GlobalFail }
		STATUS current
		DESCRIPTION
			"Input global (any kind) fail status Trap"
		::= { adl3000c01v1Traps 19 }

		-- 1.3.6.1.4.1.10106.2.1.1.247001
		hvd3000c01v1Traps OBJECT IDENTIFIER ::= { albalaTraps 247001 }

		-- 1.3.6.1.4.1.10106.2.1.1.247001.3
		hvd3000c01v1NoSigATrap NOTIFICATION-TYPE
		OBJECTS { trapCounter, hvd3000c01v1Index, hvd3000c01v1NoSigA }
		STATUS current
		DESCRIPTION
			"Input signal status Trap"
		::= { hvd3000c01v1Traps 5 }

		-- 1.3.6.1.4.1.10106.2.1.1.247001.3
		hvd3000c01v1UnlockATrap NOTIFICATION-TYPE
		OBJECTS { trapCounter, hvd3000c01v1Index, hvd3000c01v1UnlockA }
		STATUS current
		DESCRIPTION
			"Indicates signal unlock fail Trap"
		::= { hvd3000c01v1Traps 9 }

		-- 1.3.6.1.4.1.10106.2.1.1.247001.3
		hvd3000c01v1NoSigBTrap NOTIFICATION-TYPE
		OBJECTS { trapCounter, hvd3000c01v1Index, hvd3000c01v1NoSigB }
		STATUS current
		DESCRIPTION
			"Input signal status Trap"
		::= { hvd3000c01v1Traps 11 }

		-- 1.3.6.1.4.1.10106.2.1.1.247001.3
		hvd3000c01v1UnlockBTrap NOTIFICATION-TYPE
		OBJECTS { trapCounter, hvd3000c01v1Index, hvd3000c01v1UnlockB }
		STATUS current
		DESCRIPTION
			"Indicates signal unlock fail Trap"
		::= { hvd3000c01v1Traps 15 }

		-- 1.3.6.1.4.1.10106.2.1.1.247002
		hvd3000c01v2Traps OBJECT IDENTIFIER ::= { albalaTraps 247002 }

		-- 1.3.6.1.4.1.10106.2.1.1.247002.3
		hvd3000c01v2NoSigATrap NOTIFICATION-TYPE
		OBJECTS { trapCounter, hvd3000c01v2Index, hvd3000c01v2NoSigA }
		STATUS current
		DESCRIPTION
			"Input signal status Trap"
		::= { hvd3000c01v2Traps 5 }

		-- 1.3.6.1.4.1.10106.2.1.1.247002.3
		hvd3000c01v2UnlockATrap NOTIFICATION-TYPE
		OBJECTS { trapCounter, hvd3000c01v2Index, hvd3000c01v2UnlockA }
		STATUS current
		DESCRIPTION
			"Indicates signal unlock fail Trap"
		::= { hvd3000c01v2Traps 7 }

		-- 1.3.6.1.4.1.10106.2.1.1.247002.3
		hvd3000c01v2NoSigBTrap NOTIFICATION-TYPE
		OBJECTS { trapCounter, hvd3000c01v2Index, hvd3000c01v2NoSigB }
		STATUS current
		DESCRIPTION
			"Input signal status Trap"
		::= { hvd3000c01v2Traps 9 }

		-- 1.3.6.1.4.1.10106.2.1.1.247002.3
		hvd3000c01v2UnlockBTrap NOTIFICATION-TYPE
		OBJECTS { trapCounter, hvd3000c01v2Index, hvd3000c01v2UnlockB }
		STATUS current
		DESCRIPTION
			"Indicates signal unlock fail Trap"
		::= { hvd3000c01v2Traps 11 }

		-- 1.3.6.1.4.1.10106.2.1.1.247101
		hdt3000c01v1Traps OBJECT IDENTIFIER ::= { albalaTraps 247101 }

		-- 1.3.6.1.4.1.10106.2.1.1.247101.3
		hdt3000c01v1NoSigATrap NOTIFICATION-TYPE
		OBJECTS { trapCounter, hdt3000c01v1Index, hdt3000c01v1NoSigA }
		STATUS current
		DESCRIPTION
			"Input signal status Trap"
		::= { hdt3000c01v1Traps 3 }

		-- 1.3.6.1.4.1.10106.2.1.1.247101.3
		hdt3000c01v1UnlockATrap NOTIFICATION-TYPE
		OBJECTS { trapCounter, hdt3000c01v1Index, hdt3000c01v1UnlockA }
		STATUS current
		DESCRIPTION
			"Indicates signal unlock fail Trap"
		::= { hdt3000c01v1Traps 5 }

		-- 1.3.6.1.4.1.10106.2.1.1.247101.3
		hdt3000c01v1LaserFailATrap NOTIFICATION-TYPE
		OBJECTS { trapCounter, hdt3000c01v1Index, hdt3000c01v1LaserFailA }
		STATUS current
		DESCRIPTION
			"Laser status Trap"
		::= { hdt3000c01v1Traps 7 }

		-- 1.3.6.1.4.1.10106.2.1.1.247101.3
		hdt3000c01v1NoSigBTrap NOTIFICATION-TYPE
		OBJECTS { trapCounter, hdt3000c01v1Index, hdt3000c01v1NoSigB }
		STATUS current
		DESCRIPTION
			"Input signal status Trap"
		::= { hdt3000c01v1Traps 11 }

		-- 1.3.6.1.4.1.10106.2.1.1.247101.3
		hdt3000c01v1UnlockBTrap NOTIFICATION-TYPE
		OBJECTS { trapCounter, hdt3000c01v1Index, hdt3000c01v1UnlockB }
		STATUS current
		DESCRIPTION
			"Indicates signal unlock fail Trap"
		::= { hdt3000c01v1Traps 13 }

		-- 1.3.6.1.4.1.10106.2.1.1.247101.3
		hdt3000c01v1LaserFailBTrap NOTIFICATION-TYPE
		OBJECTS { trapCounter, hdt3000c01v1Index, hdt3000c01v1LaserFailB }
		STATUS current
		DESCRIPTION
			"Laser status Trap"
		::= { hdt3000c01v1Traps 15 }

		-- 1.3.6.1.4.1.10106.2.1.1.247201
		hdr3000c01v1Traps OBJECT IDENTIFIER ::= { albalaTraps 247201 }

		-- 1.3.6.1.4.1.10106.2.1.1.247201.3
		hdr3000c01v1NoSigEATrap NOTIFICATION-TYPE
		OBJECTS { trapCounter, hdr3000c01v1Index, hdr3000c01v1NoSigEA }
		STATUS current
		DESCRIPTION
			"Electrical input signal status Trap"
		::= { hdr3000c01v1Traps 7 }

		-- 1.3.6.1.4.1.10106.2.1.1.247201.3
		hdr3000c01v1NoSigEOATrap NOTIFICATION-TYPE
		OBJECTS { trapCounter, hdr3000c01v1Index, hdr3000c01v1NoSigEOA }
		STATUS current
		DESCRIPTION
			"Optical input signal status Trap"
		::= { hdr3000c01v1Traps 11 }

		-- 1.3.6.1.4.1.10106.2.1.1.247201.3
		hdr3000c01v1UnlockATrap NOTIFICATION-TYPE
		OBJECTS { trapCounter, hdr3000c01v1Index, hdr3000c01v1UnlockA }
		STATUS current
		DESCRIPTION
			"Indicates signal unlock fail Trap"
		::= { hdr3000c01v1Traps 13 }

		-- 1.3.6.1.4.1.10106.2.1.1.247201.3
		hdr3000c01v1NoSigEBTrap NOTIFICATION-TYPE
		OBJECTS { trapCounter, hdr3000c01v1Index, hdr3000c01v1NoSigEB }
		STATUS current
		DESCRIPTION
			"Electrical input signal status Trap"
		::= { hdr3000c01v1Traps 17 }

		-- 1.3.6.1.4.1.10106.2.1.1.247201.3
		hdr3000c01v1NoSigOBTrap NOTIFICATION-TYPE
		OBJECTS { trapCounter, hdr3000c01v1Index, hdr3000c01v1NoSigOB }
		STATUS current
		DESCRIPTION
			"Optical input signal status Trap"
		::= { hdr3000c01v1Traps 21 }

		-- 1.3.6.1.4.1.10106.2.1.1.247201.3
		hdr3000c01v1UnlockBTrap NOTIFICATION-TYPE
		OBJECTS { trapCounter, hdr3000c01v1Index, hdr3000c01v1UnlockB }
		STATUS current
		DESCRIPTION
			"Indicates signal unlock fail Trap"
		::= { hdr3000c01v1Traps 23 }

		-- 1.3.6.1.4.1.10106.2.1.1.259501
		dli3001c01v1Traps OBJECT IDENTIFIER ::= { albalaTraps 259501 }

		-- 1.3.6.1.4.1.10106.2.1.1.259501.3
		dli3001c01v1NoSigTrap NOTIFICATION-TYPE
		OBJECTS { trapCounter, dli3001c01v1Index, dli3001c01v1NoSig }
		STATUS current
		DESCRIPTION
			"SDI input signal status Trap"
		::= { dli3001c01v1Traps 87 }

		-- 1.3.6.1.4.1.10106.2.1.1.259501.3
		dli3001c01v1AudioFr0ErrTrap NOTIFICATION-TYPE
		OBJECTS { trapCounter, dli3001c01v1Index, dli3001c01v1AudioFr0Err }
		STATUS current
		DESCRIPTION
			"Indicates that there is no valid audio in the frame 0 Trap"
		::= { dli3001c01v1Traps 91 }

		-- 1.3.6.1.4.1.10106.2.1.1.259501.3
		dli3001c01v1AudioFr1ErrTrap NOTIFICATION-TYPE
		OBJECTS { trapCounter, dli3001c01v1Index, dli3001c01v1AudioFr1Err }
		STATUS current
		DESCRIPTION
			"Indicates that there is no valid audio in the frame 1 Trap"
		::= { dli3001c01v1Traps 93 }

		-- 1.3.6.1.4.1.10106.2.1.1.259601
		eap3001c01v1Traps OBJECT IDENTIFIER ::= { albalaTraps 259601 }

		-- 1.3.6.1.4.1.10106.2.1.1.259601.3
		eap3001c01v1NoSigATrap NOTIFICATION-TYPE
		OBJECTS { trapCounter, eap3001c01v1Index, eap3001c01v1NoSigA }
		STATUS current
		DESCRIPTION
			"SDI input signal status Trap"
		::= { eap3001c01v1Traps 325 }

		-- 1.3.6.1.4.1.10106.2.1.1.259601.3
		eap3001c01v1AudioFr0ErrATrap NOTIFICATION-TYPE
		OBJECTS { trapCounter, eap3001c01v1Index, eap3001c01v1AudioFr0ErrA }
		STATUS current
		DESCRIPTION
			"Indicates that there is no valid audio in the frame 0 Trap"
		::= { eap3001c01v1Traps 329 }

		-- 1.3.6.1.4.1.10106.2.1.1.259601.3
		eap3001c01v1AudioFr1ErrATrap NOTIFICATION-TYPE
		OBJECTS { trapCounter, eap3001c01v1Index, eap3001c01v1AudioFr1ErrA }
		STATUS current
		DESCRIPTION
			"Indicates that there is no valid audio in the frame 1 Trap"
		::= { eap3001c01v1Traps 331 }

		-- 1.3.6.1.4.1.10106.2.1.1.259601.3
		eap3001c01v1NoSigBTrap NOTIFICATION-TYPE
		OBJECTS { trapCounter, eap3001c01v1Index, eap3001c01v1NoSigB }
		STATUS current
		DESCRIPTION
			"SDI input signal status Trap"
		::= { eap3001c01v1Traps 341 }

		-- 1.3.6.1.4.1.10106.2.1.1.259601.3
		eap3001c01v1AudioFr0ErrBTrap NOTIFICATION-TYPE
		OBJECTS { trapCounter, eap3001c01v1Index, eap3001c01v1AudioFr0ErrB }
		STATUS current
		DESCRIPTION
			"Indicates that there is no valid audio in the frame 0 Trap"
		::= { eap3001c01v1Traps 345 }

		-- 1.3.6.1.4.1.10106.2.1.1.259601.3
		eap3001c01v1AudioFr1ErrBTrap NOTIFICATION-TYPE
		OBJECTS { trapCounter, eap3001c01v1Index, eap3001c01v1AudioFr1ErrB }
		STATUS current
		DESCRIPTION
			"Indicates that there is no valid audio in the frame 1 Trap"
		::= { eap3001c01v1Traps 347 }

		-- 1.3.6.1.4.1.10106.2.1.1.272801
		ur-3100r05v1Traps OBJECT IDENTIFIER ::= { albalaTraps 272801 }

		-- 1.3.6.1.4.1.10106.2.1.1.272801.3
		ur-3100r05v1PwrFailRTrap NOTIFICATION-TYPE
		OBJECTS { trapCounter, ur-3100r05v1Index, ur-3100r05v1PwrFailR }
		STATUS current
		DESCRIPTION
			"Indicates the rigth power supply status Trap"
		::= { ur-3100r05v1Traps 3 }

		-- 1.3.6.1.4.1.10106.2.1.1.272801.3
		ur-3100r05v1PwrFailLTrap NOTIFICATION-TYPE
		OBJECTS { trapCounter, ur-3100r05v1Index, ur-3100r05v1PwrFailL }
		STATUS current
		DESCRIPTION
			"Indicates the left power supply status Trap"
		::= { ur-3100r05v1Traps 5 }

		-- 1.3.6.1.4.1.10106.2.1.1.272901
		ur-3100r06v1Traps OBJECT IDENTIFIER ::= { albalaTraps 272901 }

		-- 1.3.6.1.4.1.10106.2.1.1.272901.3
		ur-3100r06v1PwrFailRTrap NOTIFICATION-TYPE
		OBJECTS { trapCounter, ur-3100r06v1Index, ur-3100r06v1PwrFailR }
		STATUS current
		DESCRIPTION
			"Indicates the rigth power supply status Trap"
		::= { ur-3100r06v1Traps 3 }

		-- 1.3.6.1.4.1.10106.2.1.1.272901.3
		ur-3100r06v1PwrFailLTrap NOTIFICATION-TYPE
		OBJECTS { trapCounter, ur-3100r06v1Index, ur-3100r06v1PwrFailL }
		STATUS current
		DESCRIPTION
			"Indicates the left power supply status Trap"
		::= { ur-3100r06v1Traps 5 }

		-- 1.3.6.1.4.1.10106.2.1.1.273001
		ur-3100r07v1Traps OBJECT IDENTIFIER ::= { albalaTraps 273001 }

		-- 1.3.6.1.4.1.10106.2.1.1.273001.3
		ur-3100r07v1PwrFailRTrap NOTIFICATION-TYPE
		OBJECTS { trapCounter, ur-3100r07v1Index, ur-3100r07v1PwrFailR }
		STATUS current
		DESCRIPTION
			"Indicates the rigth power supply status Trap"
		::= { ur-3100r07v1Traps 3 }

		-- 1.3.6.1.4.1.10106.2.1.1.273001.3
		ur-3100r07v1PwrFailLTrap NOTIFICATION-TYPE
		OBJECTS { trapCounter, ur-3100r07v1Index, ur-3100r07v1PwrFailL }
		STATUS current
		DESCRIPTION
			"Indicates the left power supply status Trap"
		::= { ur-3100r07v1Traps 5 }

		-- 1.3.6.1.4.1.10106.2.1.1.273101
		ur-3100r08v1Traps OBJECT IDENTIFIER ::= { albalaTraps 273101 }

		-- 1.3.6.1.4.1.10106.2.1.1.273101.3
		ur-3100r08v1PwrFailRTrap NOTIFICATION-TYPE
		OBJECTS { trapCounter, ur-3100r08v1Index, ur-3100r08v1PwrFailR }
		STATUS current
		DESCRIPTION
			"Indicates the rigth power supply status Trap"
		::= { ur-3100r08v1Traps 3 }

		-- 1.3.6.1.4.1.10106.2.1.1.273101.3
		ur-3100r08v1PwrFailLTrap NOTIFICATION-TYPE
		OBJECTS { trapCounter, ur-3100r08v1Index, ur-3100r08v1PwrFailL }
		STATUS current
		DESCRIPTION
			"Indicates the left power supply status Trap"
		::= { ur-3100r08v1Traps 5 }

		-- 1.3.6.1.4.1.10106.2.1.1.273201
		ur-3100r09v1Traps OBJECT IDENTIFIER ::= { albalaTraps 273201 }

		-- 1.3.6.1.4.1.10106.2.1.1.273201.3
		ur-3100r09v1PwrFailRTrap NOTIFICATION-TYPE
		OBJECTS { trapCounter, ur-3100r09v1Index, ur-3100r09v1PwrFailR }
		STATUS current
		DESCRIPTION
			"Indicates the rigth power supply status Trap"
		::= { ur-3100r09v1Traps 3 }

		-- 1.3.6.1.4.1.10106.2.1.1.273201.3
		ur-3100r09v1PwrFailLTrap NOTIFICATION-TYPE
		OBJECTS { trapCounter, ur-3100r09v1Index, ur-3100r09v1PwrFailL }
		STATUS current
		DESCRIPTION
			"Indicates the left power supply status Trap"
		::= { ur-3100r09v1Traps 5 }

		-- 1.3.6.1.4.1.10106.2.1.1.274401
		dvm3001c01v1Traps OBJECT IDENTIFIER ::= { albalaTraps 274401 }

		-- 1.3.6.1.4.1.10106.2.1.1.274401.3
		dvm3001c01v1NoSigATrap NOTIFICATION-TYPE
		OBJECTS { trapCounter, dvm3001c01v1Index, dvm3001c01v1NoSigA }
		STATUS current
		DESCRIPTION
			"Input signal status Trap"
		::= { dvm3001c01v1Traps 21 }

		-- 1.3.6.1.4.1.10106.2.1.1.274401.3
		dvm3001c01v1NoSigBTrap NOTIFICATION-TYPE
		OBJECTS { trapCounter, dvm3001c01v1Index, dvm3001c01v1NoSigB }
		STATUS current
		DESCRIPTION
			"Input signal status Trap"
		::= { dvm3001c01v1Traps 23 }

		-- 1.3.6.1.4.1.10106.2.1.1.274401.3
		dvm3001c01v1UnlockATrap NOTIFICATION-TYPE
		OBJECTS { trapCounter, dvm3001c01v1Index, dvm3001c01v1UnlockA }
		STATUS current
		DESCRIPTION
			"Indicates signal unlock fail Trap"
		::= { dvm3001c01v1Traps 29 }

		-- 1.3.6.1.4.1.10106.2.1.1.274401.3
		dvm3001c01v1UnlockBTrap NOTIFICATION-TYPE
		OBJECTS { trapCounter, dvm3001c01v1Index, dvm3001c01v1UnlockB }
		STATUS current
		DESCRIPTION
			"Indicates signal unlock fail Trap"
		::= { dvm3001c01v1Traps 31 }

		-- 1.3.6.1.4.1.10106.2.1.1.275101
		dsw3001c01v1Traps OBJECT IDENTIFIER ::= { albalaTraps 275101 }

		-- 1.3.6.1.4.1.10106.2.1.1.275101.3
		dsw3001c01v1ModeTrap NOTIFICATION-TYPE
		OBJECTS { trapCounter, dsw3001c01v1Index, dsw3001c01v1Mode }
		STATUS current
		DESCRIPTION
			"Allows selecting the switching mode Trap"
		::= { dsw3001c01v1Traps 3 }

		-- 1.3.6.1.4.1.10106.2.1.1.275101.3
		dsw3001c01v1InputTrap NOTIFICATION-TYPE
		OBJECTS { trapCounter, dsw3001c01v1Index, dsw3001c01v1Input }
		STATUS current
		DESCRIPTION
			"Selected input Trap"
		::= { dsw3001c01v1Traps 13 }

		-- 1.3.6.1.4.1.10106.2.1.1.275101.3
		dsw3001c01v1VideoFailMTrap NOTIFICATION-TYPE
		OBJECTS { trapCounter, dsw3001c01v1Index, dsw3001c01v1VideoFailM }
		STATUS current
		DESCRIPTION
			"Indicates that any video fail is active in main input Trap"
		::= { dsw3001c01v1Traps 137 }

		-- 1.3.6.1.4.1.10106.2.1.1.275101.3
		dsw3001c01v1VideoFailRTrap NOTIFICATION-TYPE
		OBJECTS { trapCounter, dsw3001c01v1Index, dsw3001c01v1VideoFailR }
		STATUS current
		DESCRIPTION
			"Indicates that any video fail is active in reserve input Trap"
		::= { dsw3001c01v1Traps 139 }

		-- 1.3.6.1.4.1.10106.2.1.1.275101.3
		dsw3001c01v1AudioFailMTrap NOTIFICATION-TYPE
		OBJECTS { trapCounter, dsw3001c01v1Index, dsw3001c01v1AudioFailM }
		STATUS current
		DESCRIPTION
			"Indicates that any audio fail is active in main input Trap"
		::= { dsw3001c01v1Traps 141 }

		-- 1.3.6.1.4.1.10106.2.1.1.275101.3
		dsw3001c01v1AudioFailRTrap NOTIFICATION-TYPE
		OBJECTS { trapCounter, dsw3001c01v1Index, dsw3001c01v1AudioFailR }
		STATUS current
		DESCRIPTION
			"Indicates that any audio fail is active in reserve input Trap"
		::= { dsw3001c01v1Traps 143 }

		-- 1.3.6.1.4.1.10106.2.1.1.278601
		dvb3001c01v1Traps OBJECT IDENTIFIER ::= { albalaTraps 278601 }

		-- 1.3.6.1.4.1.10106.2.1.1.278601.3
		dvb3001c01v1NoSigATrap NOTIFICATION-TYPE
		OBJECTS { trapCounter, dvb3001c01v1Index, dvb3001c01v1NoSigA }
		STATUS current
		DESCRIPTION
			"Input signal status Trap"
		::= { dvb3001c01v1Traps 3 }

		-- 1.3.6.1.4.1.10106.2.1.1.278601.3
		dvb3001c01v1NoSigBTrap NOTIFICATION-TYPE
		OBJECTS { trapCounter, dvb3001c01v1Index, dvb3001c01v1NoSigB }
		STATUS current
		DESCRIPTION
			"Input signal status Trap"
		::= { dvb3001c01v1Traps 7 }

		-- 1.3.6.1.4.1.10106.2.1.1.282401
		dvm3001c02v1Traps OBJECT IDENTIFIER ::= { albalaTraps 282401 }

		-- 1.3.6.1.4.1.10106.2.1.1.282401.3
		dvm3001c02v1NoSigATrap NOTIFICATION-TYPE
		OBJECTS { trapCounter, dvm3001c02v1Index, dvm3001c02v1NoSigA }
		STATUS current
		DESCRIPTION
			"Input signal status Trap"
		::= { dvm3001c02v1Traps 21 }

		-- 1.3.6.1.4.1.10106.2.1.1.282401.3
		dvm3001c02v1NoSigBTrap NOTIFICATION-TYPE
		OBJECTS { trapCounter, dvm3001c02v1Index, dvm3001c02v1NoSigB }
		STATUS current
		DESCRIPTION
			"Input signal status Trap"
		::= { dvm3001c02v1Traps 23 }

		-- 1.3.6.1.4.1.10106.2.1.1.282401.3
		dvm3001c02v1UnlockATrap NOTIFICATION-TYPE
		OBJECTS { trapCounter, dvm3001c02v1Index, dvm3001c02v1UnlockA }
		STATUS current
		DESCRIPTION
			"Indicates signal unlock fail Trap"
		::= { dvm3001c02v1Traps 29 }

		-- 1.3.6.1.4.1.10106.2.1.1.282401.3
		dvm3001c02v1UnlockBTrap NOTIFICATION-TYPE
		OBJECTS { trapCounter, dvm3001c02v1Index, dvm3001c02v1UnlockB }
		STATUS current
		DESCRIPTION
			"Indicates signal unlock fail Trap"
		::= { dvm3001c02v1Traps 31 }

		-- 1.3.6.1.4.1.10106.2.1.1.283901
		dvb3001c02v1Traps OBJECT IDENTIFIER ::= { albalaTraps 283901 }

		-- 1.3.6.1.4.1.10106.2.1.1.283901.3
		dvb3001c02v1NoSigATrap NOTIFICATION-TYPE
		OBJECTS { trapCounter, dvb3001c02v1Index, dvb3001c02v1NoSigA }
		STATUS current
		DESCRIPTION
			"Input signal status Trap"
		::= { dvb3001c02v1Traps 3 }

		-- 1.3.6.1.4.1.10106.2.1.1.283901.3
		dvb3001c02v1NoSigBTrap NOTIFICATION-TYPE
		OBJECTS { trapCounter, dvb3001c02v1Index, dvb3001c02v1NoSigB }
		STATUS current
		DESCRIPTION
			"Input signal status Trap"
		::= { dvb3001c02v1Traps 7 }

		-- 1.3.6.1.4.1.10106.2.1.1.286201
		gps3002c01v1Traps OBJECT IDENTIFIER ::= { albalaTraps 286201 }

		-- 1.3.6.1.4.1.10106.2.1.1.286201.3
		gps3002c01v1RedundanceModeTrap NOTIFICATION-TYPE
		OBJECTS { trapCounter, gps3002c01v1Index, gps3002c01v1RedundanceMode }
		STATUS current
		DESCRIPTION
			"Allows selecting the redundance mode Trap"
		::= { gps3002c01v1Traps 5 }

		-- 1.3.6.1.4.1.10106.2.1.1.286201.3
		gps3002c01v1HoldoverStatTrap NOTIFICATION-TYPE
		OBJECTS { trapCounter, gps3002c01v1Index, gps3002c01v1HoldoverStat }
		STATUS current
		DESCRIPTION
			"Indicates if the module is locked to GPS or to reference or it is in holdover mode Trap"
		::= { gps3002c01v1Traps 9 }

		-- 1.3.6.1.4.1.10106.2.1.1.286201.3
		gps3002c01v1MaintenanceFailTrap NOTIFICATION-TYPE
		OBJECTS { trapCounter, gps3002c01v1Index, gps3002c01v1MaintenanceFail }
		STATUS current
		DESCRIPTION
			"Indicates that a service operation is required Trap"
		::= { gps3002c01v1Traps 11 }

		-- 1.3.6.1.4.1.10106.2.1.1.286201.3
		gps3002c01v1OutputsMutedTrap NOTIFICATION-TYPE
		OBJECTS { trapCounter, gps3002c01v1Index, gps3002c01v1OutputsMuted }
		STATUS current
		DESCRIPTION
			"Indicates f the module outputs are disabled (reserve module) Trap"
		::= { gps3002c01v1Traps 13 }

		-- 1.3.6.1.4.1.10106.2.1.1.286201.3
		gps3002c01v11ppsDisableTrap NOTIFICATION-TYPE
		OBJECTS { trapCounter, gps3002c01v1Index, gps3002c01v11ppsDisable }
		STATUS current
		DESCRIPTION
			"Indicates if the 1PPS output is muted Trap"
		::= { gps3002c01v1Traps 15 }

		-- 1.3.6.1.4.1.10106.2.1.1.286201.3
		gps3002c01v1AntenaStatTrap NOTIFICATION-TYPE
		OBJECTS { trapCounter, gps3002c01v1Index, gps3002c01v1AntenaStat }
		STATUS current
		DESCRIPTION
			"Antenna connection status Trap"
		::= { gps3002c01v1Traps 21 }

		-- 1.3.6.1.4.1.10106.2.1.1.290701
		gps3002c03v1Traps OBJECT IDENTIFIER ::= { albalaTraps 290701 }

		-- 1.3.6.1.4.1.10106.2.1.1.290701.3
		gps3002c03v1RedundanceModeTrap NOTIFICATION-TYPE
		OBJECTS { trapCounter, gps3002c03v1Index, gps3002c03v1RedundanceMode }
		STATUS current
		DESCRIPTION
			"Allows selecting the redundance mode Trap"
		::= { gps3002c03v1Traps 5 }

		-- 1.3.6.1.4.1.10106.2.1.1.290701.3
		gps3002c03v1HoldoverStatTrap NOTIFICATION-TYPE
		OBJECTS { trapCounter, gps3002c03v1Index, gps3002c03v1HoldoverStat }
		STATUS current
		DESCRIPTION
			"Indicates if the module is locked to GPS or to reference or it is in holdover mode Trap"
		::= { gps3002c03v1Traps 9 }

		-- 1.3.6.1.4.1.10106.2.1.1.290701.3
		gps3002c03v1MaintenanceFailTrap NOTIFICATION-TYPE
		OBJECTS { trapCounter, gps3002c03v1Index, gps3002c03v1MaintenanceFail }
		STATUS current
		DESCRIPTION
			"Indicates that a service operation is required Trap"
		::= { gps3002c03v1Traps 11 }

		-- 1.3.6.1.4.1.10106.2.1.1.290701.3
		gps3002c03v1OutputsMutedTrap NOTIFICATION-TYPE
		OBJECTS { trapCounter, gps3002c03v1Index, gps3002c03v1OutputsMuted }
		STATUS current
		DESCRIPTION
			"Indicates f the module outputs are disabled (reserve module) Trap"
		::= { gps3002c03v1Traps 13 }

		-- 1.3.6.1.4.1.10106.2.1.1.290701.3
		gps3002c03v11ppsDisableTrap NOTIFICATION-TYPE
		OBJECTS { trapCounter, gps3002c03v1Index, gps3002c03v11ppsDisable }
		STATUS current
		DESCRIPTION
			"Indicates if the 1PPS output is muted Trap"
		::= { gps3002c03v1Traps 15 }

		-- 1.3.6.1.4.1.10106.2.1.1.290701.3
		gps3002c03v1AntenaStatTrap NOTIFICATION-TYPE
		OBJECTS { trapCounter, gps3002c03v1Index, gps3002c03v1AntenaStat }
		STATUS current
		DESCRIPTION
			"Antenna connection status Trap"
		::= { gps3002c03v1Traps 21 }

		-- 1.3.6.1.4.1.10106.2.1.1.290901
		tsm3001c01v1Traps OBJECT IDENTIFIER ::= { albalaTraps 290901 }

		-- 1.3.6.1.4.1.10106.2.1.1.290901.3
		tsm3001c01v1NoTsNatTrap NOTIFICATION-TYPE
		OBJECTS { trapCounter, tsm3001c01v1Index, tsm3001c01v1NoTsNat }
		STATUS current
		DESCRIPTION
			"Indicates no national TS signal Trap"
		::= { tsm3001c01v1Traps 3 }

		-- 1.3.6.1.4.1.10106.2.1.1.290901.3
		tsm3001c01v1NoReplacTrap NOTIFICATION-TYPE
		OBJECTS { trapCounter, tsm3001c01v1Index, tsm3001c01v1NoReplac }
		STATUS current
		DESCRIPTION
			"Indicates that no replacement is performed Trap"
		::= { tsm3001c01v1Traps 5 }

		-- 1.3.6.1.4.1.10106.2.1.1.290901.3
		tsm3001c01v1BadTsidNatTrap NOTIFICATION-TYPE
		OBJECTS { trapCounter, tsm3001c01v1Index, tsm3001c01v1BadTsidNat }
		STATUS current
		DESCRIPTION
			"Indicates that the national TS ID is not correct Trap"
		::= { tsm3001c01v1Traps 7 }

		-- 1.3.6.1.4.1.10106.2.1.1.290901.3
		tsm3001c01v1NoTsRegTrap NOTIFICATION-TYPE
		OBJECTS { trapCounter, tsm3001c01v1Index, tsm3001c01v1NoTsReg }
		STATUS current
		DESCRIPTION
			"Indicates no regional TS signal Trap"
		::= { tsm3001c01v1Traps 17 }

		-- 1.3.6.1.4.1.10106.2.1.1.290901.3
		tsm3001c01v1BadTsidRegTrap NOTIFICATION-TYPE
		OBJECTS { trapCounter, tsm3001c01v1Index, tsm3001c01v1BadTsidReg }
		STATUS current
		DESCRIPTION
			"Indicates that the regional TS ID is not correct Trap"
		::= { tsm3001c01v1Traps 19 }

		-- 1.3.6.1.4.1.10106.2.1.1.315301
		dsw3000c05v1Traps OBJECT IDENTIFIER ::= { albalaTraps 315301 }

		-- 1.3.6.1.4.1.10106.2.1.1.315301.3
		dsw3000c05v1ModeTrap NOTIFICATION-TYPE
		OBJECTS { trapCounter, dsw3000c05v1Index, dsw3000c05v1Mode }
		STATUS current
		DESCRIPTION
			"Allows selecting the switching mode Trap"
		::= { dsw3000c05v1Traps 3 }

		-- 1.3.6.1.4.1.10106.2.1.1.315301.3
		dsw3000c05v1InputTrap NOTIFICATION-TYPE
		OBJECTS { trapCounter, dsw3000c05v1Index, dsw3000c05v1Input }
		STATUS current
		DESCRIPTION
			"Selected input Trap"
		::= { dsw3000c05v1Traps 7 }

		-- 1.3.6.1.4.1.10106.2.1.1.315301.3
		dsw3000c05v1MainFailTrap NOTIFICATION-TYPE
		OBJECTS { trapCounter, dsw3000c05v1Index, dsw3000c05v1MainFail }
		STATUS current
		DESCRIPTION
			"Main input status Trap"
		::= { dsw3000c05v1Traps 9 }

		-- 1.3.6.1.4.1.10106.2.1.1.315301.3
		dsw3000c05v1ExtMainFailTrap NOTIFICATION-TYPE
		OBJECTS { trapCounter, dsw3000c05v1Index, dsw3000c05v1ExtMainFail }
		STATUS current
		DESCRIPTION
			"Main external input fail status Trap"
		::= { dsw3000c05v1Traps 11 }

		-- 1.3.6.1.4.1.10106.2.1.1.315301.3
		dsw3000c05v1ResFailTrap NOTIFICATION-TYPE
		OBJECTS { trapCounter, dsw3000c05v1Index, dsw3000c05v1ResFail }
		STATUS current
		DESCRIPTION
			"Reserve input status Trap"
		::= { dsw3000c05v1Traps 13 }

		-- 1.3.6.1.4.1.10106.2.1.1.315301.3
		dsw3000c05v1ExtResFailTrap NOTIFICATION-TYPE
		OBJECTS { trapCounter, dsw3000c05v1Index, dsw3000c05v1ExtResFail }
		STATUS current
		DESCRIPTION
			"Reserve external input fail status Trap"
		::= { dsw3000c05v1Traps 15 }

		-- 1.3.6.1.4.1.10106.2.1.1.315301.3
		dsw3000c05v1AuxFailTrap NOTIFICATION-TYPE
		OBJECTS { trapCounter, dsw3000c05v1Index, dsw3000c05v1AuxFail }
		STATUS current
		DESCRIPTION
			"Auxiliar input status Trap"
		::= { dsw3000c05v1Traps 17 }

		-- 1.3.6.1.4.1.10106.2.1.1.315301.3
		dsw3000c05v1ExtAuxFailTrap NOTIFICATION-TYPE
		OBJECTS { trapCounter, dsw3000c05v1Index, dsw3000c05v1ExtAuxFail }
		STATUS current
		DESCRIPTION
			"Auxiliar external input fail status Trap"
		::= { dsw3000c05v1Traps 19 }

		-- 1.3.6.1.4.1.10106.2.1.1.316801
		ssw3000c01v1Traps OBJECT IDENTIFIER ::= { albalaTraps 316801 }

		-- 1.3.6.1.4.1.10106.2.1.1.316801.3
		ssw3000c01v1ModeTrap NOTIFICATION-TYPE
		OBJECTS { trapCounter, ssw3000c01v1Index, ssw3000c01v1Mode }
		STATUS current
		DESCRIPTION
			"Allows selecting the switching mode Trap"
		::= { ssw3000c01v1Traps 3 }

		-- 1.3.6.1.4.1.10106.2.1.1.316801.3
		ssw3000c01v1DvbTModeTrap NOTIFICATION-TYPE
		OBJECTS { trapCounter, ssw3000c01v1Index, ssw3000c01v1DvbTMode }
		STATUS current
		DESCRIPTION
			"Selects DVB-T mode. Seamless operation is only possible in DVB-T mode Trap"
		::= { ssw3000c01v1Traps 7 }

		-- 1.3.6.1.4.1.10106.2.1.1.316801.3
		ssw3000c01v1InputTrap NOTIFICATION-TYPE
		OBJECTS { trapCounter, ssw3000c01v1Index, ssw3000c01v1Input }
		STATUS current
		DESCRIPTION
			"Selected input Trap"
		::= { ssw3000c01v1Traps 9 }

		-- 1.3.6.1.4.1.10106.2.1.1.316801.3
		ssw3000c01v1OutDelayTrap NOTIFICATION-TYPE
		OBJECTS { trapCounter, ssw3000c01v1Index, ssw3000c01v1OutDelay }
		STATUS current
		DESCRIPTION
			"Output delay refered to 1PPS reference Trap"
		::= { ssw3000c01v1Traps 13 }

		-- 1.3.6.1.4.1.10106.2.1.1.316801.3
		ssw3000c01v1MainFailTrap NOTIFICATION-TYPE
		OBJECTS { trapCounter, ssw3000c01v1Index, ssw3000c01v1MainFail }
		STATUS current
		DESCRIPTION
			"Main input status Trap"
		::= { ssw3000c01v1Traps 15 }

		-- 1.3.6.1.4.1.10106.2.1.1.316801.3
		ssw3000c01v1ExtMainFailTrap NOTIFICATION-TYPE
		OBJECTS { trapCounter, ssw3000c01v1Index, ssw3000c01v1ExtMainFail }
		STATUS current
		DESCRIPTION
			"Main external input fail status Trap"
		::= { ssw3000c01v1Traps 17 }

		-- 1.3.6.1.4.1.10106.2.1.1.316801.3
		ssw3000c01v1ResFailTrap NOTIFICATION-TYPE
		OBJECTS { trapCounter, ssw3000c01v1Index, ssw3000c01v1ResFail }
		STATUS current
		DESCRIPTION
			"Reserve input status Trap"
		::= { ssw3000c01v1Traps 19 }

		-- 1.3.6.1.4.1.10106.2.1.1.316801.3
		ssw3000c01v1ExtResFailTrap NOTIFICATION-TYPE
		OBJECTS { trapCounter, ssw3000c01v1Index, ssw3000c01v1ExtResFail }
		STATUS current
		DESCRIPTION
			"Reserve external input fail status Trap"
		::= { ssw3000c01v1Traps 21 }

		-- 1.3.6.1.4.1.10106.2.1.1.316801.3
		ssw3000c01v1AuxFailTrap NOTIFICATION-TYPE
		OBJECTS { trapCounter, ssw3000c01v1Index, ssw3000c01v1AuxFail }
		STATUS current
		DESCRIPTION
			"Auxiliar input status Trap"
		::= { ssw3000c01v1Traps 23 }

		-- 1.3.6.1.4.1.10106.2.1.1.316801.3
		ssw3000c01v1ExtAuxFailTrap NOTIFICATION-TYPE
		OBJECTS { trapCounter, ssw3000c01v1Index, ssw3000c01v1ExtAuxFail }
		STATUS current
		DESCRIPTION
			"Auxiliar external input fail status Trap"
		::= { ssw3000c01v1Traps 25 }

		-- 1.3.6.1.4.1.10106.2.1.1.316801.3
		ssw3000c01v11ppsFailTrap NOTIFICATION-TYPE
		OBJECTS { trapCounter, ssw3000c01v1Index, ssw3000c01v11ppsFail }
		STATUS current
		DESCRIPTION
			"1PPS reference input status Trap"
		::= { ssw3000c01v1Traps 27 }

		-- 1.3.6.1.4.1.10106.2.1.1.316801.3
		ssw3000c01v1GlobalSeamTrap NOTIFICATION-TYPE
		OBJECTS { trapCounter, ssw3000c01v1Index, ssw3000c01v1GlobalSeam }
		STATUS current
		DESCRIPTION
			"Global seamles switching capability Trap"
		::= { ssw3000c01v1Traps 35 }

		-- 1.3.6.1.4.1.10106.2.1.1.320501
		pdc3002c01v1Traps OBJECT IDENTIFIER ::= { albalaTraps 320501 }

		-- 1.3.6.1.4.1.10106.2.1.1.320501.3
		pdc3002c01v1UnlockATrap NOTIFICATION-TYPE
		OBJECTS { trapCounter, pdc3002c01v1Index, pdc3002c01v1UnlockA }
		STATUS current
		DESCRIPTION
			"Indicates VCXO unlock fail Trap"
		::= { pdc3002c01v1Traps 15 }

		-- 1.3.6.1.4.1.10106.2.1.1.320501.3
		pdc3002c01v1UnlockBTrap NOTIFICATION-TYPE
		OBJECTS { trapCounter, pdc3002c01v1Index, pdc3002c01v1UnlockB }
		STATUS current
		DESCRIPTION
			"Indicates VCXO unlock fail Trap"
		::= { pdc3002c01v1Traps 17 }

		-- 1.3.6.1.4.1.10106.2.1.1.320501.3
		pdc3002c01v1NoSigATrap NOTIFICATION-TYPE
		OBJECTS { trapCounter, pdc3002c01v1Index, pdc3002c01v1NoSigA }
		STATUS current
		DESCRIPTION
			"Composite video signal status Trap"
		::= { pdc3002c01v1Traps 19 }

		-- 1.3.6.1.4.1.10106.2.1.1.320501.3
		pdc3002c01v1NoSigBTrap NOTIFICATION-TYPE
		OBJECTS { trapCounter, pdc3002c01v1Index, pdc3002c01v1NoSigB }
		STATUS current
		DESCRIPTION
			"Composite video signal status Trap"
		::= { pdc3002c01v1Traps 21 }

		-- 1.3.6.1.4.1.10106.2.1.1.324201
		vct3000c11v1Traps OBJECT IDENTIFIER ::= { albalaTraps 324201 }

		-- 1.3.6.1.4.1.10106.2.1.1.324201.3
		vct3000c11v1ModeTrap NOTIFICATION-TYPE
		OBJECTS { trapCounter, vct3000c11v1Index, vct3000c11v1Mode }
		STATUS current
		DESCRIPTION
			"Allows selecting the switching mode Trap"
		::= { vct3000c11v1Traps 3 }

		-- 1.3.6.1.4.1.10106.2.1.1.324201.3
		vct3000c11v1InputTrap NOTIFICATION-TYPE
		OBJECTS { trapCounter, vct3000c11v1Index, vct3000c11v1Input }
		STATUS current
		DESCRIPTION
			"Selected input Trap"
		::= { vct3000c11v1Traps 7 }

		-- 1.3.6.1.4.1.10106.2.1.1.324201.3
		vct3000c11v1MainFailTrap NOTIFICATION-TYPE
		OBJECTS { trapCounter, vct3000c11v1Index, vct3000c11v1MainFail }
		STATUS current
		DESCRIPTION
			"Main input status Trap"
		::= { vct3000c11v1Traps 13 }

		-- 1.3.6.1.4.1.10106.2.1.1.324201.3
		vct3000c11v1ResFailTrap NOTIFICATION-TYPE
		OBJECTS { trapCounter, vct3000c11v1Index, vct3000c11v1ResFail }
		STATUS current
		DESCRIPTION
			"Reserve input status Trap"
		::= { vct3000c11v1Traps 15 }

		-- 1.3.6.1.4.1.10106.2.1.1.324201.3
		vct3000c11v1AuxFailTrap NOTIFICATION-TYPE
		OBJECTS { trapCounter, vct3000c11v1Index, vct3000c11v1AuxFail }
		STATUS current
		DESCRIPTION
			"Auxiliar input status Trap"
		::= { vct3000c11v1Traps 17 }

		-- 1.3.6.1.4.1.10106.2.1.1.324301
		vct3000c12v1Traps OBJECT IDENTIFIER ::= { albalaTraps 324301 }

		-- 1.3.6.1.4.1.10106.2.1.1.324301.3
		vct3000c12v1ModeTrap NOTIFICATION-TYPE
		OBJECTS { trapCounter, vct3000c12v1Index, vct3000c12v1Mode }
		STATUS current
		DESCRIPTION
			"Allows selecting the switching mode Trap"
		::= { vct3000c12v1Traps 3 }

		-- 1.3.6.1.4.1.10106.2.1.1.324301.3
		vct3000c12v1InputTrap NOTIFICATION-TYPE
		OBJECTS { trapCounter, vct3000c12v1Index, vct3000c12v1Input }
		STATUS current
		DESCRIPTION
			"Selected input Trap"
		::= { vct3000c12v1Traps 7 }

		-- 1.3.6.1.4.1.10106.2.1.1.324301.3
		vct3000c12v1MainFailTrap NOTIFICATION-TYPE
		OBJECTS { trapCounter, vct3000c12v1Index, vct3000c12v1MainFail }
		STATUS current
		DESCRIPTION
			"Main input status Trap"
		::= { vct3000c12v1Traps 13 }

		-- 1.3.6.1.4.1.10106.2.1.1.324301.3
		vct3000c12v1ResFailTrap NOTIFICATION-TYPE
		OBJECTS { trapCounter, vct3000c12v1Index, vct3000c12v1ResFail }
		STATUS current
		DESCRIPTION
			"Reserve input status Trap"
		::= { vct3000c12v1Traps 15 }

		-- 1.3.6.1.4.1.10106.2.1.1.324301.3
		vct3000c12v1AuxFailTrap NOTIFICATION-TYPE
		OBJECTS { trapCounter, vct3000c12v1Index, vct3000c12v1AuxFail }
		STATUS current
		DESCRIPTION
			"Auxiliar input status Trap"
		::= { vct3000c12v1Traps 17 }

		-- 1.3.6.1.4.1.10106.2.1.1.324401
		vct3000c14v1Traps OBJECT IDENTIFIER ::= { albalaTraps 324401 }

		-- 1.3.6.1.4.1.10106.2.1.1.324401.3
		vct3000c14v1ModeTrap NOTIFICATION-TYPE
		OBJECTS { trapCounter, vct3000c14v1Index, vct3000c14v1Mode }
		STATUS current
		DESCRIPTION
			"Allows selecting the switching mode Trap"
		::= { vct3000c14v1Traps 3 }

		-- 1.3.6.1.4.1.10106.2.1.1.324401.3
		vct3000c14v1InputTrap NOTIFICATION-TYPE
		OBJECTS { trapCounter, vct3000c14v1Index, vct3000c14v1Input }
		STATUS current
		DESCRIPTION
			"Selected input Trap"
		::= { vct3000c14v1Traps 7 }

		-- 1.3.6.1.4.1.10106.2.1.1.324401.3
		vct3000c14v1MainFailTrap NOTIFICATION-TYPE
		OBJECTS { trapCounter, vct3000c14v1Index, vct3000c14v1MainFail }
		STATUS current
		DESCRIPTION
			"Main input status Trap"
		::= { vct3000c14v1Traps 13 }

		-- 1.3.6.1.4.1.10106.2.1.1.324401.3
		vct3000c14v1ResFailTrap NOTIFICATION-TYPE
		OBJECTS { trapCounter, vct3000c14v1Index, vct3000c14v1ResFail }
		STATUS current
		DESCRIPTION
			"Reserve input status Trap"
		::= { vct3000c14v1Traps 15 }

		-- 1.3.6.1.4.1.10106.2.1.1.324401.3
		vct3000c14v1AuxFailTrap NOTIFICATION-TYPE
		OBJECTS { trapCounter, vct3000c14v1Index, vct3000c14v1AuxFail }
		STATUS current
		DESCRIPTION
			"Auxiliar input status Trap"
		::= { vct3000c14v1Traps 17 }

		-- 1.3.6.1.4.1.10106.2.1.1.324501
		vct3000c15v1Traps OBJECT IDENTIFIER ::= { albalaTraps 324501 }

		-- 1.3.6.1.4.1.10106.2.1.1.324501.3
		vct3000c15v1ModeTrap NOTIFICATION-TYPE
		OBJECTS { trapCounter, vct3000c15v1Index, vct3000c15v1Mode }
		STATUS current
		DESCRIPTION
			"Allows selecting the switching mode Trap"
		::= { vct3000c15v1Traps 3 }

		-- 1.3.6.1.4.1.10106.2.1.1.324501.3
		vct3000c15v1InputTrap NOTIFICATION-TYPE
		OBJECTS { trapCounter, vct3000c15v1Index, vct3000c15v1Input }
		STATUS current
		DESCRIPTION
			"Selected input Trap"
		::= { vct3000c15v1Traps 7 }

		-- 1.3.6.1.4.1.10106.2.1.1.324501.3
		vct3000c15v1MainFailTrap NOTIFICATION-TYPE
		OBJECTS { trapCounter, vct3000c15v1Index, vct3000c15v1MainFail }
		STATUS current
		DESCRIPTION
			"Main input status Trap"
		::= { vct3000c15v1Traps 13 }

		-- 1.3.6.1.4.1.10106.2.1.1.324501.3
		vct3000c15v1ResFailTrap NOTIFICATION-TYPE
		OBJECTS { trapCounter, vct3000c15v1Index, vct3000c15v1ResFail }
		STATUS current
		DESCRIPTION
			"Reserve input status Trap"
		::= { vct3000c15v1Traps 15 }

		-- 1.3.6.1.4.1.10106.2.1.1.324501.3
		vct3000c15v1AuxFailTrap NOTIFICATION-TYPE
		OBJECTS { trapCounter, vct3000c15v1Index, vct3000c15v1AuxFail }
		STATUS current
		DESCRIPTION
			"Auxiliar input status Trap"
		::= { vct3000c15v1Traps 17 }

		-- 1.3.6.1.4.1.10106.2.1.1.327001
		vtl3000c01v1Traps OBJECT IDENTIFIER ::= { albalaTraps 327001 }

		-- 1.3.6.1.4.1.10106.2.1.1.327001.3
		vtl3000c01v1NoSignalTrap NOTIFICATION-TYPE
		OBJECTS { trapCounter, vtl3000c01v1Index, vtl3000c01v1NoSignal }
		STATUS current
		DESCRIPTION
			"SDI input signal status Trap"
		::= { vtl3000c01v1Traps 5 }

		-- 1.3.6.1.4.1.10106.2.1.1.327001.3
		vtl3000c01v1DupTcTrap NOTIFICATION-TYPE
		OBJECTS { trapCounter, vtl3000c01v1Index, vtl3000c01v1DupTc }
		STATUS current
		DESCRIPTION
			"Duplicated time code Trap"
		::= { vtl3000c01v1Traps 19 }

		-- 1.3.6.1.4.1.10106.2.1.1.327001.3
		vtl3000c01v1LostTcTrap NOTIFICATION-TYPE
		OBJECTS { trapCounter, vtl3000c01v1Index, vtl3000c01v1LostTc }
		STATUS current
		DESCRIPTION
			"Discontinuous time code Trap"
		::= { vtl3000c01v1Traps 21 }

		-- 1.3.6.1.4.1.10106.2.1.1.327001.3
		vtl3000c01v1NoTcFrameTrap NOTIFICATION-TYPE
		OBJECTS { trapCounter, vtl3000c01v1Index, vtl3000c01v1NoTcFrame }
		STATUS current
		DESCRIPTION
			"Missing time code Trap"
		::= { vtl3000c01v1Traps 23 }

		-- 1.3.6.1.4.1.10106.2.1.1.328401
		tle3001c01v1Traps OBJECT IDENTIFIER ::= { albalaTraps 328401 }

		-- 1.3.6.1.4.1.10106.2.1.1.328401.3
		tle3001c01v1Gpi1Trap NOTIFICATION-TYPE
		OBJECTS { trapCounter, tle3001c01v1Index, tle3001c01v1Gpi1 }
		STATUS current
		DESCRIPTION
			"GPI1 status Trap"
		::= { tle3001c01v1Traps 31 }

		-- 1.3.6.1.4.1.10106.2.1.1.328401.3
		tle3001c01v1Gpi2Trap NOTIFICATION-TYPE
		OBJECTS { trapCounter, tle3001c01v1Index, tle3001c01v1Gpi2 }
		STATUS current
		DESCRIPTION
			"GPI2 status Trap"
		::= { tle3001c01v1Traps 33 }

		-- 1.3.6.1.4.1.10106.2.1.1.328401.3
		tle3001c01v1Gpi3Trap NOTIFICATION-TYPE
		OBJECTS { trapCounter, tle3001c01v1Index, tle3001c01v1Gpi3 }
		STATUS current
		DESCRIPTION
			"GPI3 status Trap"
		::= { tle3001c01v1Traps 35 }

		-- 1.3.6.1.4.1.10106.2.1.1.328401.3
		tle3001c01v1Gpi4Trap NOTIFICATION-TYPE
		OBJECTS { trapCounter, tle3001c01v1Index, tle3001c01v1Gpi4 }
		STATUS current
		DESCRIPTION
			"GPI4 status Trap"
		::= { tle3001c01v1Traps 37 }

		-- 1.3.6.1.4.1.10106.2.1.1.328401.3
		tle3001c01v1RedBoardTrap NOTIFICATION-TYPE
		OBJECTS { trapCounter, tle3001c01v1Index, tle3001c01v1RedBoard }
		STATUS current
		DESCRIPTION
			"Indicates that there are two modules in redundant configuration Trap"
		::= { tle3001c01v1Traps 39 }

		-- 1.3.6.1.4.1.10106.2.1.1.328401.3
		tle3001c01v1EthLinkTrap NOTIFICATION-TYPE
		OBJECTS { trapCounter, tle3001c01v1Index, tle3001c01v1EthLink }
		STATUS current
		DESCRIPTION
			"Indicates that the Ethernet link is OK Trap"
		::= { tle3001c01v1Traps 41 }

		-- 1.3.6.1.4.1.10106.2.1.1.328401.3
		tle3001c01v1EthRedActTrap NOTIFICATION-TYPE
		OBJECTS { trapCounter, tle3001c01v1Index, tle3001c01v1EthRedAct }
		STATUS current
		DESCRIPTION
			"Indicates that this is the active module of the redundant configuration Trap"
		::= { tle3001c01v1Traps 43 }

		-- 1.3.6.1.4.1.10106.2.1.1.339901
		gvd3000c01v1Traps OBJECT IDENTIFIER ::= { albalaTraps 339901 }

		-- 1.3.6.1.4.1.10106.2.1.1.339901.3
		gvd3000c01v1LosATrap NOTIFICATION-TYPE
		OBJECTS { trapCounter, gvd3000c01v1Index, gvd3000c01v1LosA }
		STATUS current
		DESCRIPTION
			"Indicates that a LOS fail has been detected Trap"
		::= { gvd3000c01v1Traps 7 }

		-- 1.3.6.1.4.1.10106.2.1.1.339901.3
		gvd3000c01v1AisATrap NOTIFICATION-TYPE
		OBJECTS { trapCounter, gvd3000c01v1Index, gvd3000c01v1AisA }
		STATUS current
		DESCRIPTION
			"Indicates that a AIS fail has been detected Trap"
		::= { gvd3000c01v1Traps 9 }

		-- 1.3.6.1.4.1.10106.2.1.1.339901.3
		gvd3000c01v1LosBTrap NOTIFICATION-TYPE
		OBJECTS { trapCounter, gvd3000c01v1Index, gvd3000c01v1LosB }
		STATUS current
		DESCRIPTION
			"Indicates that a LOS fail has been detected Trap"
		::= { gvd3000c01v1Traps 11 }

		-- 1.3.6.1.4.1.10106.2.1.1.339901.3
		gvd3000c01v1AisBTrap NOTIFICATION-TYPE
		OBJECTS { trapCounter, gvd3000c01v1Index, gvd3000c01v1AisB }
		STATUS current
		DESCRIPTION
			"Indicates that a AIS fail has been detected Trap"
		::= { gvd3000c01v1Traps 13 }

		-- 1.3.6.1.4.1.10106.2.1.1.343901
		htg3000c01v1Traps OBJECT IDENTIFIER ::= { albalaTraps 343901 }

		-- 1.3.6.1.4.1.10106.2.1.1.343901.3
		htg3000c01v1RefLckFailTrap NOTIFICATION-TYPE
		OBJECTS { trapCounter, htg3000c01v1Index, htg3000c01v1RefLckFail }
		STATUS current
		DESCRIPTION
			"Indicates that the module is not locked to the reference Trap"
		::= { htg3000c01v1Traps 25 }

		-- 1.3.6.1.4.1.10106.2.1.1.343901.3
		htg3000c01v1RefFailTrap NOTIFICATION-TYPE
		OBJECTS { trapCounter, htg3000c01v1Index, htg3000c01v1RefFail }
		STATUS current
		DESCRIPTION
			"Indicates that there is no reference input signal Trap"
		::= { htg3000c01v1Traps 27 }

		-- 1.3.6.1.4.1.10106.2.1.1.347601
		hvd3001c01v1Traps OBJECT IDENTIFIER ::= { albalaTraps 347601 }

		-- 1.3.6.1.4.1.10106.2.1.1.347601.3
		hvd3001c01v1NoSigATrap NOTIFICATION-TYPE
		OBJECTS { trapCounter, hvd3001c01v1Index, hvd3001c01v1NoSigA }
		STATUS current
		DESCRIPTION
			"Input signal status Trap"
		::= { hvd3001c01v1Traps 9 }

		-- 1.3.6.1.4.1.10106.2.1.1.347601.3
		hvd3001c01v1UnlockATrap NOTIFICATION-TYPE
		OBJECTS { trapCounter, hvd3001c01v1Index, hvd3001c01v1UnlockA }
		STATUS current
		DESCRIPTION
			"Indicates signal unlock fail Trap"
		::= { hvd3001c01v1Traps 11 }

		-- 1.3.6.1.4.1.10106.2.1.1.347601.3
		hvd3001c01v1LFailATrap NOTIFICATION-TYPE
		OBJECTS { trapCounter, hvd3001c01v1Index, hvd3001c01v1LFailA }
		STATUS current
		DESCRIPTION
			"Indicates a fail in laser Trap"
		::= { hvd3001c01v1Traps 13 }

		-- 1.3.6.1.4.1.10106.2.1.1.347601.3
		hvd3001c01v1NoSigBTrap NOTIFICATION-TYPE
		OBJECTS { trapCounter, hvd3001c01v1Index, hvd3001c01v1NoSigB }
		STATUS current
		DESCRIPTION
			"Input signal status Trap"
		::= { hvd3001c01v1Traps 21 }

		-- 1.3.6.1.4.1.10106.2.1.1.347601.3
		hvd3001c01v1UnlockBTrap NOTIFICATION-TYPE
		OBJECTS { trapCounter, hvd3001c01v1Index, hvd3001c01v1UnlockB }
		STATUS current
		DESCRIPTION
			"Indicates signal unlock fail Trap"
		::= { hvd3001c01v1Traps 23 }

		-- 1.3.6.1.4.1.10106.2.1.1.347601.3
		hvd3001c01v1LFailBTrap NOTIFICATION-TYPE
		OBJECTS { trapCounter, hvd3001c01v1Index, hvd3001c01v1LFailB }
		STATUS current
		DESCRIPTION
			"Indicates a fail in laser Trap"
		::= { hvd3001c01v1Traps 25 }

		-- 1.3.6.1.4.1.10106.2.1.1.350401
		vct3000c13v1Traps OBJECT IDENTIFIER ::= { albalaTraps 350401 }

		-- 1.3.6.1.4.1.10106.2.1.1.350401.3
		vct3000c13v1ModeTrap NOTIFICATION-TYPE
		OBJECTS { trapCounter, vct3000c13v1Index, vct3000c13v1Mode }
		STATUS current
		DESCRIPTION
			"Allows selecting the switching mode Trap"
		::= { vct3000c13v1Traps 3 }

		-- 1.3.6.1.4.1.10106.2.1.1.350401.3
		vct3000c13v1InputTrap NOTIFICATION-TYPE
		OBJECTS { trapCounter, vct3000c13v1Index, vct3000c13v1Input }
		STATUS current
		DESCRIPTION
			"Selected input Trap"
		::= { vct3000c13v1Traps 7 }

		-- 1.3.6.1.4.1.10106.2.1.1.350401.3
		vct3000c13v1MainFailTrap NOTIFICATION-TYPE
		OBJECTS { trapCounter, vct3000c13v1Index, vct3000c13v1MainFail }
		STATUS current
		DESCRIPTION
			"Main input status Trap"
		::= { vct3000c13v1Traps 13 }

		-- 1.3.6.1.4.1.10106.2.1.1.350401.3
		vct3000c13v1ResFailTrap NOTIFICATION-TYPE
		OBJECTS { trapCounter, vct3000c13v1Index, vct3000c13v1ResFail }
		STATUS current
		DESCRIPTION
			"Reserve input status Trap"
		::= { vct3000c13v1Traps 15 }

		-- 1.3.6.1.4.1.10106.2.1.1.350401.3
		vct3000c13v1AuxFailTrap NOTIFICATION-TYPE
		OBJECTS { trapCounter, vct3000c13v1Index, vct3000c13v1AuxFail }
		STATUS current
		DESCRIPTION
			"Auxiliar input status Trap"
		::= { vct3000c13v1Traps 17 }

		-- 1.3.6.1.4.1.10106.2.1.1.352201
		dad3002c02v1Traps OBJECT IDENTIFIER ::= { albalaTraps 352201 }

		-- 1.3.6.1.4.1.10106.2.1.1.352201.3
		dad3002c02v1LosATrap NOTIFICATION-TYPE
		OBJECTS { trapCounter, dad3002c02v1Index, dad3002c02v1LosA }
		STATUS current
		DESCRIPTION
			"Indicates that a LOS fail has been detected Trap"
		::= { dad3002c02v1Traps 3 }

		-- 1.3.6.1.4.1.10106.2.1.1.352201.3
		dad3002c02v1LosBTrap NOTIFICATION-TYPE
		OBJECTS { trapCounter, dad3002c02v1Index, dad3002c02v1LosB }
		STATUS current
		DESCRIPTION
			"Indicates that a LOS fail has been detected Trap"
		::= { dad3002c02v1Traps 5 }

		-- 1.3.6.1.4.1.10106.2.1.1.353101
		hvd3001c02v1Traps OBJECT IDENTIFIER ::= { albalaTraps 353101 }

		-- 1.3.6.1.4.1.10106.2.1.1.353101.3
		hvd3001c02v1NoSigATrap NOTIFICATION-TYPE
		OBJECTS { trapCounter, hvd3001c02v1Index, hvd3001c02v1NoSigA }
		STATUS current
		DESCRIPTION
			"Input signal status Trap"
		::= { hvd3001c02v1Traps 9 }

		-- 1.3.6.1.4.1.10106.2.1.1.353101.3
		hvd3001c02v1UnlockATrap NOTIFICATION-TYPE
		OBJECTS { trapCounter, hvd3001c02v1Index, hvd3001c02v1UnlockA }
		STATUS current
		DESCRIPTION
			"Indicates signal unlock fail Trap"
		::= { hvd3001c02v1Traps 11 }

		-- 1.3.6.1.4.1.10106.2.1.1.353101.3
		hvd3001c02v1LFailATrap NOTIFICATION-TYPE
		OBJECTS { trapCounter, hvd3001c02v1Index, hvd3001c02v1LFailA }
		STATUS current
		DESCRIPTION
			"Indicates a fail in laser Trap"
		::= { hvd3001c02v1Traps 13 }

		-- 1.3.6.1.4.1.10106.2.1.1.353101.3
		hvd3001c02v1NoSigBTrap NOTIFICATION-TYPE
		OBJECTS { trapCounter, hvd3001c02v1Index, hvd3001c02v1NoSigB }
		STATUS current
		DESCRIPTION
			"Input signal status Trap"
		::= { hvd3001c02v1Traps 21 }

		-- 1.3.6.1.4.1.10106.2.1.1.353101.3
		hvd3001c02v1UnlockBTrap NOTIFICATION-TYPE
		OBJECTS { trapCounter, hvd3001c02v1Index, hvd3001c02v1UnlockB }
		STATUS current
		DESCRIPTION
			"Indicates signal unlock fail Trap"
		::= { hvd3001c02v1Traps 23 }

		-- 1.3.6.1.4.1.10106.2.1.1.353101.3
		hvd3001c02v1LFailBTrap NOTIFICATION-TYPE
		OBJECTS { trapCounter, hvd3001c02v1Index, hvd3001c02v1LFailB }
		STATUS current
		DESCRIPTION
			"Indicates a fail in laser Trap"
		::= { hvd3001c02v1Traps 25 }

		-- 1.3.6.1.4.1.10106.2.1.1.357101
		hvd3001c03v1Traps OBJECT IDENTIFIER ::= { albalaTraps 357101 }

		-- 1.3.6.1.4.1.10106.2.1.1.357101.3
		hvd3001c03v1NoSigATrap NOTIFICATION-TYPE
		OBJECTS { trapCounter, hvd3001c03v1Index, hvd3001c03v1NoSigA }
		STATUS current
		DESCRIPTION
			"Input signal status Trap"
		::= { hvd3001c03v1Traps 9 }

		-- 1.3.6.1.4.1.10106.2.1.1.357101.3
		hvd3001c03v1UnlockATrap NOTIFICATION-TYPE
		OBJECTS { trapCounter, hvd3001c03v1Index, hvd3001c03v1UnlockA }
		STATUS current
		DESCRIPTION
			"Indicates signal unlock fail Trap"
		::= { hvd3001c03v1Traps 11 }

		-- 1.3.6.1.4.1.10106.2.1.1.357101.3
		hvd3001c03v1LFailATrap NOTIFICATION-TYPE
		OBJECTS { trapCounter, hvd3001c03v1Index, hvd3001c03v1LFailA }
		STATUS current
		DESCRIPTION
			"Indicates a fail in laser Trap"
		::= { hvd3001c03v1Traps 13 }

		-- 1.3.6.1.4.1.10106.2.1.1.357101.3
		hvd3001c03v1NoSigBTrap NOTIFICATION-TYPE
		OBJECTS { trapCounter, hvd3001c03v1Index, hvd3001c03v1NoSigB }
		STATUS current
		DESCRIPTION
			"Input signal status Trap"
		::= { hvd3001c03v1Traps 21 }

		-- 1.3.6.1.4.1.10106.2.1.1.357101.3
		hvd3001c03v1UnlockBTrap NOTIFICATION-TYPE
		OBJECTS { trapCounter, hvd3001c03v1Index, hvd3001c03v1UnlockB }
		STATUS current
		DESCRIPTION
			"Indicates signal unlock fail Trap"
		::= { hvd3001c03v1Traps 23 }

		-- 1.3.6.1.4.1.10106.2.1.1.357101.3
		hvd3001c03v1LFailBTrap NOTIFICATION-TYPE
		OBJECTS { trapCounter, hvd3001c03v1Index, hvd3001c03v1LFailB }
		STATUS current
		DESCRIPTION
			"Indicates a fail in laser Trap"
		::= { hvd3001c03v1Traps 25 }

		-- 1.3.6.1.4.1.10106.2.1.1.357201
		hvd3001c04v1Traps OBJECT IDENTIFIER ::= { albalaTraps 357201 }

		-- 1.3.6.1.4.1.10106.2.1.1.357201.3
		hvd3001c04v1NoSigATrap NOTIFICATION-TYPE
		OBJECTS { trapCounter, hvd3001c04v1Index, hvd3001c04v1NoSigA }
		STATUS current
		DESCRIPTION
			"Input signal status Trap"
		::= { hvd3001c04v1Traps 9 }

		-- 1.3.6.1.4.1.10106.2.1.1.357201.3
		hvd3001c04v1UnlockATrap NOTIFICATION-TYPE
		OBJECTS { trapCounter, hvd3001c04v1Index, hvd3001c04v1UnlockA }
		STATUS current
		DESCRIPTION
			"Indicates signal unlock fail Trap"
		::= { hvd3001c04v1Traps 11 }

		-- 1.3.6.1.4.1.10106.2.1.1.357201.3
		hvd3001c04v1LFailATrap NOTIFICATION-TYPE
		OBJECTS { trapCounter, hvd3001c04v1Index, hvd3001c04v1LFailA }
		STATUS current
		DESCRIPTION
			"Indicates a fail in laser Trap"
		::= { hvd3001c04v1Traps 13 }

		-- 1.3.6.1.4.1.10106.2.1.1.357201.3
		hvd3001c04v1NoSigBTrap NOTIFICATION-TYPE
		OBJECTS { trapCounter, hvd3001c04v1Index, hvd3001c04v1NoSigB }
		STATUS current
		DESCRIPTION
			"Input signal status Trap"
		::= { hvd3001c04v1Traps 21 }

		-- 1.3.6.1.4.1.10106.2.1.1.357201.3
		hvd3001c04v1UnlockBTrap NOTIFICATION-TYPE
		OBJECTS { trapCounter, hvd3001c04v1Index, hvd3001c04v1UnlockB }
		STATUS current
		DESCRIPTION
			"Indicates signal unlock fail Trap"
		::= { hvd3001c04v1Traps 23 }

		-- 1.3.6.1.4.1.10106.2.1.1.357201.3
		hvd3001c04v1LFailBTrap NOTIFICATION-TYPE
		OBJECTS { trapCounter, hvd3001c04v1Index, hvd3001c04v1LFailB }
		STATUS current
		DESCRIPTION
			"Indicates a fail in laser Trap"
		::= { hvd3001c04v1Traps 25 }

		-- 1.3.6.1.4.1.10106.2.1.1.357501
		hfs3000c01v1Traps OBJECT IDENTIFIER ::= { albalaTraps 357501 }

		-- 1.3.6.1.4.1.10106.2.1.1.357501.3
		hfs3000c01v1NoSigATrap NOTIFICATION-TYPE
		OBJECTS { trapCounter, hfs3000c01v1Index, hfs3000c01v1NoSigA }
		STATUS current
		DESCRIPTION
			"Indicates SDI signal fail Trap"
		::= { hfs3000c01v1Traps 43 }

		-- 1.3.6.1.4.1.10106.2.1.1.357501.3
		hfs3000c01v1UnlockATrap NOTIFICATION-TYPE
		OBJECTS { trapCounter, hfs3000c01v1Index, hfs3000c01v1UnlockA }
		STATUS current
		DESCRIPTION
			"Indicates signal unlock Trap"
		::= { hfs3000c01v1Traps 45 }

		-- 1.3.6.1.4.1.10106.2.1.1.357501.3
		hfs3000c01v1EdhCrcATrap NOTIFICATION-TYPE
		OBJECTS { trapCounter, hfs3000c01v1Index, hfs3000c01v1EdhCrcA }
		STATUS current
		DESCRIPTION
			"Indicates presence of EDH/CRC errors Trap"
		::= { hfs3000c01v1Traps 47 }

		-- 1.3.6.1.4.1.10106.2.1.1.357501.3
		hfs3000c01v1GpiFailATrap NOTIFICATION-TYPE
		OBJECTS { trapCounter, hfs3000c01v1Index, hfs3000c01v1GpiFailA }
		STATUS current
		DESCRIPTION
			"Indicates external fail Trap"
		::= { hfs3000c01v1Traps 49 }

		-- 1.3.6.1.4.1.10106.2.1.1.357501.3
		hfs3000c01v1NoSigBTrap NOTIFICATION-TYPE
		OBJECTS { trapCounter, hfs3000c01v1Index, hfs3000c01v1NoSigB }
		STATUS current
		DESCRIPTION
			"Indicates SDI signal fail Trap"
		::= { hfs3000c01v1Traps 51 }

		-- 1.3.6.1.4.1.10106.2.1.1.357501.3
		hfs3000c01v1UnlockBTrap NOTIFICATION-TYPE
		OBJECTS { trapCounter, hfs3000c01v1Index, hfs3000c01v1UnlockB }
		STATUS current
		DESCRIPTION
			"Indicates signal unlock Trap"
		::= { hfs3000c01v1Traps 53 }

		-- 1.3.6.1.4.1.10106.2.1.1.357501.3
		hfs3000c01v1EdhCrcBTrap NOTIFICATION-TYPE
		OBJECTS { trapCounter, hfs3000c01v1Index, hfs3000c01v1EdhCrcB }
		STATUS current
		DESCRIPTION
			"Indicates presence of EDH/CRC errors Trap"
		::= { hfs3000c01v1Traps 55 }

		-- 1.3.6.1.4.1.10106.2.1.1.357501.3
		hfs3000c01v1GpiFailBTrap NOTIFICATION-TYPE
		OBJECTS { trapCounter, hfs3000c01v1Index, hfs3000c01v1GpiFailB }
		STATUS current
		DESCRIPTION
			"Indicates external fail Trap"
		::= { hfs3000c01v1Traps 57 }

		-- 1.3.6.1.4.1.10106.2.1.1.357501.3
		hfs3000c01v1NoRefTrap NOTIFICATION-TYPE
		OBJECTS { trapCounter, hfs3000c01v1Index, hfs3000c01v1NoRef }
		STATUS current
		DESCRIPTION
			"Indicates reference signal fail Trap"
		::= { hfs3000c01v1Traps 59 }

		-- 1.3.6.1.4.1.10106.2.1.1.357501.3
		hfs3000c01v1RefAUnlockTrap NOTIFICATION-TYPE
		OBJECTS { trapCounter, hfs3000c01v1Index, hfs3000c01v1RefAUnlock }
		STATUS current
		DESCRIPTION
			"Indicates reference signal unlock fail Trap"
		::= { hfs3000c01v1Traps 61 }

		-- 1.3.6.1.4.1.10106.2.1.1.357501.3
		hfs3000c01v1RefBUnlockTrap NOTIFICATION-TYPE
		OBJECTS { trapCounter, hfs3000c01v1Index, hfs3000c01v1RefBUnlock }
		STATUS current
		DESCRIPTION
			"Indicates reference signal unlock fail Trap"
		::= { hfs3000c01v1Traps 63 }

		-- 1.3.6.1.4.1.10106.2.1.1.357502
		hfs3000c01v2Traps OBJECT IDENTIFIER ::= { albalaTraps 357502 }

		-- 1.3.6.1.4.1.10106.2.1.1.357502.3
		hfs3000c01v2NoSigATrap NOTIFICATION-TYPE
		OBJECTS { trapCounter, hfs3000c01v2Index, hfs3000c01v2NoSigA }
		STATUS current
		DESCRIPTION
			"Indicates SDI signal fail Trap"
		::= { hfs3000c01v2Traps 95 }

		-- 1.3.6.1.4.1.10106.2.1.1.357502.3
		hfs3000c01v2UnlockATrap NOTIFICATION-TYPE
		OBJECTS { trapCounter, hfs3000c01v2Index, hfs3000c01v2UnlockA }
		STATUS current
		DESCRIPTION
			"Indicates signal unlock Trap"
		::= { hfs3000c01v2Traps 97 }

		-- 1.3.6.1.4.1.10106.2.1.1.357502.3
		hfs3000c01v2EdhCrcATrap NOTIFICATION-TYPE
		OBJECTS { trapCounter, hfs3000c01v2Index, hfs3000c01v2EdhCrcA }
		STATUS current
		DESCRIPTION
			"Indicates presence of EDH/CRC errors Trap"
		::= { hfs3000c01v2Traps 99 }

		-- 1.3.6.1.4.1.10106.2.1.1.357502.3
		hfs3000c01v2GpiFailATrap NOTIFICATION-TYPE
		OBJECTS { trapCounter, hfs3000c01v2Index, hfs3000c01v2GpiFailA }
		STATUS current
		DESCRIPTION
			"Indicates external fail Trap"
		::= { hfs3000c01v2Traps 101 }

		-- 1.3.6.1.4.1.10106.2.1.1.357502.3
		hfs3000c01v2NoSigBTrap NOTIFICATION-TYPE
		OBJECTS { trapCounter, hfs3000c01v2Index, hfs3000c01v2NoSigB }
		STATUS current
		DESCRIPTION
			"Indicates SDI signal fail Trap"
		::= { hfs3000c01v2Traps 103 }

		-- 1.3.6.1.4.1.10106.2.1.1.357502.3
		hfs3000c01v2UnlockBTrap NOTIFICATION-TYPE
		OBJECTS { trapCounter, hfs3000c01v2Index, hfs3000c01v2UnlockB }
		STATUS current
		DESCRIPTION
			"Indicates signal unlock Trap"
		::= { hfs3000c01v2Traps 105 }

		-- 1.3.6.1.4.1.10106.2.1.1.357502.3
		hfs3000c01v2EdhCrcBTrap NOTIFICATION-TYPE
		OBJECTS { trapCounter, hfs3000c01v2Index, hfs3000c01v2EdhCrcB }
		STATUS current
		DESCRIPTION
			"Indicates presence of EDH/CRC errors Trap"
		::= { hfs3000c01v2Traps 107 }

		-- 1.3.6.1.4.1.10106.2.1.1.357502.3
		hfs3000c01v2GpiFailBTrap NOTIFICATION-TYPE
		OBJECTS { trapCounter, hfs3000c01v2Index, hfs3000c01v2GpiFailB }
		STATUS current
		DESCRIPTION
			"Indicates external fail Trap"
		::= { hfs3000c01v2Traps 109 }

		-- 1.3.6.1.4.1.10106.2.1.1.357502.3
		hfs3000c01v2NoRefTrap NOTIFICATION-TYPE
		OBJECTS { trapCounter, hfs3000c01v2Index, hfs3000c01v2NoRef }
		STATUS current
		DESCRIPTION
			"Indicates reference signal fail Trap"
		::= { hfs3000c01v2Traps 111 }

		-- 1.3.6.1.4.1.10106.2.1.1.357502.3
		hfs3000c01v2RefAUnlockTrap NOTIFICATION-TYPE
		OBJECTS { trapCounter, hfs3000c01v2Index, hfs3000c01v2RefAUnlock }
		STATUS current
		DESCRIPTION
			"Indicates reference signal unlock fail Trap"
		::= { hfs3000c01v2Traps 113 }

		-- 1.3.6.1.4.1.10106.2.1.1.357502.3
		hfs3000c01v2RefBUnlockTrap NOTIFICATION-TYPE
		OBJECTS { trapCounter, hfs3000c01v2Index, hfs3000c01v2RefBUnlock }
		STATUS current
		DESCRIPTION
			"Indicates reference signal unlock fail Trap"
		::= { hfs3000c01v2Traps 115 }

		-- 1.3.6.1.4.1.10106.2.1.1.358101
		hde3000c01v1Traps OBJECT IDENTIFIER ::= { albalaTraps 358101 }

		-- 1.3.6.1.4.1.10106.2.1.1.358101.3
		hde3000c01v1NoSignalATrap NOTIFICATION-TYPE
		OBJECTS { trapCounter, hde3000c01v1Index, hde3000c01v1NoSignalA }
		STATUS current
		DESCRIPTION
			"There is no SDI signal or the format is not supported Trap"
		::= { hde3000c01v1Traps 181 }

		-- 1.3.6.1.4.1.10106.2.1.1.358101.3
		hde3000c01v1UnlockATrap NOTIFICATION-TYPE
		OBJECTS { trapCounter, hde3000c01v1Index, hde3000c01v1UnlockA }
		STATUS current
		DESCRIPTION
			"Indicates signal unlock fail Trap"
		::= { hde3000c01v1Traps 183 }

		-- 1.3.6.1.4.1.10106.2.1.1.358101.3
		hde3000c01v1EdhErrorATrap NOTIFICATION-TYPE
		OBJECTS { trapCounter, hde3000c01v1Index, hde3000c01v1EdhErrorA }
		STATUS current
		DESCRIPTION
			"There are EDH/CRC errors on SDI signal Trap"
		::= { hde3000c01v1Traps 185 }

		-- 1.3.6.1.4.1.10106.2.1.1.358101.3
		hde3000c01v1AesFailATrap NOTIFICATION-TYPE
		OBJECTS { trapCounter, hde3000c01v1Index, hde3000c01v1AesFailA }
		STATUS current
		DESCRIPTION
			"There is no valid audio in AES inputs Trap"
		::= { hde3000c01v1Traps 187 }

		-- 1.3.6.1.4.1.10106.2.1.1.358101.3
		hde3000c01v1DeemFailATrap NOTIFICATION-TYPE
		OBJECTS { trapCounter, hde3000c01v1Index, hde3000c01v1DeemFailA }
		STATUS current
		DESCRIPTION
			"There is no valid deembedded audio Trap"
		::= { hde3000c01v1Traps 189 }

		-- 1.3.6.1.4.1.10106.2.1.1.358101.3
		hde3000c01v1AesOvlATrap NOTIFICATION-TYPE
		OBJECTS { trapCounter, hde3000c01v1Index, hde3000c01v1AesOvlA }
		STATUS current
		DESCRIPTION
			"There is overload or silence in AES outputs Trap"
		::= { hde3000c01v1Traps 191 }

		-- 1.3.6.1.4.1.10106.2.1.1.358101.3
		hde3000c01v1DeemOvlATrap NOTIFICATION-TYPE
		OBJECTS { trapCounter, hde3000c01v1Index, hde3000c01v1DeemOvlA }
		STATUS current
		DESCRIPTION
			"There is overload or silence in embed audio Trap"
		::= { hde3000c01v1Traps 193 }

		-- 1.3.6.1.4.1.10106.2.1.1.358101.3
		hde3000c01v1NoSignalBTrap NOTIFICATION-TYPE
		OBJECTS { trapCounter, hde3000c01v1Index, hde3000c01v1NoSignalB }
		STATUS current
		DESCRIPTION
			"There is no SDI signal or the format is not supported Trap"
		::= { hde3000c01v1Traps 197 }

		-- 1.3.6.1.4.1.10106.2.1.1.358101.3
		hde3000c01v1UnlockBTrap NOTIFICATION-TYPE
		OBJECTS { trapCounter, hde3000c01v1Index, hde3000c01v1UnlockB }
		STATUS current
		DESCRIPTION
			"Indicates signal unlock fail Trap"
		::= { hde3000c01v1Traps 199 }

		-- 1.3.6.1.4.1.10106.2.1.1.358101.3
		hde3000c01v1EdhErrorBTrap NOTIFICATION-TYPE
		OBJECTS { trapCounter, hde3000c01v1Index, hde3000c01v1EdhErrorB }
		STATUS current
		DESCRIPTION
			"There are EDH/CRC errors on SDI signal Trap"
		::= { hde3000c01v1Traps 201 }

		-- 1.3.6.1.4.1.10106.2.1.1.358101.3
		hde3000c01v1AesFailBTrap NOTIFICATION-TYPE
		OBJECTS { trapCounter, hde3000c01v1Index, hde3000c01v1AesFailB }
		STATUS current
		DESCRIPTION
			"There is no valid audio in AES inputs Trap"
		::= { hde3000c01v1Traps 203 }

		-- 1.3.6.1.4.1.10106.2.1.1.358101.3
		hde3000c01v1DeemFailBTrap NOTIFICATION-TYPE
		OBJECTS { trapCounter, hde3000c01v1Index, hde3000c01v1DeemFailB }
		STATUS current
		DESCRIPTION
			"There is no valid deembedded audio Trap"
		::= { hde3000c01v1Traps 205 }

		-- 1.3.6.1.4.1.10106.2.1.1.358101.3
		hde3000c01v1AesOvlBTrap NOTIFICATION-TYPE
		OBJECTS { trapCounter, hde3000c01v1Index, hde3000c01v1AesOvlB }
		STATUS current
		DESCRIPTION
			"There is overload or silence in AES outputs Trap"
		::= { hde3000c01v1Traps 207 }

		-- 1.3.6.1.4.1.10106.2.1.1.358101.3
		hde3000c01v1DeemOvlBTrap NOTIFICATION-TYPE
		OBJECTS { trapCounter, hde3000c01v1Index, hde3000c01v1DeemOvlB }
		STATUS current
		DESCRIPTION
			"There is overload or silence in embed audio Trap"
		::= { hde3000c01v1Traps 209 }

		-- 1.3.6.1.4.1.10106.2.1.1.359901
		hae3000c01v1Traps OBJECT IDENTIFIER ::= { albalaTraps 359901 }

		-- 1.3.6.1.4.1.10106.2.1.1.359901.3
		hae3000c01v1NoSignalATrap NOTIFICATION-TYPE
		OBJECTS { trapCounter, hae3000c01v1Index, hae3000c01v1NoSignalA }
		STATUS current
		DESCRIPTION
			"There is no SDI signal or the format is not supported Trap"
		::= { hae3000c01v1Traps 139 }

		-- 1.3.6.1.4.1.10106.2.1.1.359901.3
		hae3000c01v1UnlockATrap NOTIFICATION-TYPE
		OBJECTS { trapCounter, hae3000c01v1Index, hae3000c01v1UnlockA }
		STATUS current
		DESCRIPTION
			"Indicates signal unlock fail Trap"
		::= { hae3000c01v1Traps 141 }

		-- 1.3.6.1.4.1.10106.2.1.1.359901.3
		hae3000c01v1EdhErrorATrap NOTIFICATION-TYPE
		OBJECTS { trapCounter, hae3000c01v1Index, hae3000c01v1EdhErrorA }
		STATUS current
		DESCRIPTION
			"There are EDH/CRC errors on SDI signal Trap"
		::= { hae3000c01v1Traps 143 }

		-- 1.3.6.1.4.1.10106.2.1.1.359901.3
		hae3000c01v1AesFailATrap NOTIFICATION-TYPE
		OBJECTS { trapCounter, hae3000c01v1Index, hae3000c01v1AesFailA }
		STATUS current
		DESCRIPTION
			"Sampling rate is not valid Trap"
		::= { hae3000c01v1Traps 145 }

		-- 1.3.6.1.4.1.10106.2.1.1.359901.3
		hae3000c01v1DeemFailATrap NOTIFICATION-TYPE
		OBJECTS { trapCounter, hae3000c01v1Index, hae3000c01v1DeemFailA }
		STATUS current
		DESCRIPTION
			"There is no valid deembedded audio Trap"
		::= { hae3000c01v1Traps 147 }

		-- 1.3.6.1.4.1.10106.2.1.1.359901.3
		hae3000c01v1DeemOvlATrap NOTIFICATION-TYPE
		OBJECTS { trapCounter, hae3000c01v1Index, hae3000c01v1DeemOvlA }
		STATUS current
		DESCRIPTION
			"There is overload or silence in embed audio Trap"
		::= { hae3000c01v1Traps 149 }

		-- 1.3.6.1.4.1.10106.2.1.1.359901.3
		hae3000c01v1ClippingATrap NOTIFICATION-TYPE
		OBJECTS { trapCounter, hae3000c01v1Index, hae3000c01v1ClippingA }
		STATUS current
		DESCRIPTION
			"Analog input clipping Trap"
		::= { hae3000c01v1Traps 151 }

		-- 1.3.6.1.4.1.10106.2.1.1.359901.3
		hae3000c01v1NoSignalBTrap NOTIFICATION-TYPE
		OBJECTS { trapCounter, hae3000c01v1Index, hae3000c01v1NoSignalB }
		STATUS current
		DESCRIPTION
			"There is no SDI signal or the format is not supported Trap"
		::= { hae3000c01v1Traps 155 }

		-- 1.3.6.1.4.1.10106.2.1.1.359901.3
		hae3000c01v1UnlockBTrap NOTIFICATION-TYPE
		OBJECTS { trapCounter, hae3000c01v1Index, hae3000c01v1UnlockB }
		STATUS current
		DESCRIPTION
			"Indicates signal unlock fail Trap"
		::= { hae3000c01v1Traps 157 }

		-- 1.3.6.1.4.1.10106.2.1.1.359901.3
		hae3000c01v1EdhErrorBTrap NOTIFICATION-TYPE
		OBJECTS { trapCounter, hae3000c01v1Index, hae3000c01v1EdhErrorB }
		STATUS current
		DESCRIPTION
			"There are EDH/CRC errors on SDI signal Trap"
		::= { hae3000c01v1Traps 159 }

		-- 1.3.6.1.4.1.10106.2.1.1.359901.3
		hae3000c01v1AesFailBTrap NOTIFICATION-TYPE
		OBJECTS { trapCounter, hae3000c01v1Index, hae3000c01v1AesFailB }
		STATUS current
		DESCRIPTION
			"Sampling rate is not valid Trap"
		::= { hae3000c01v1Traps 161 }

		-- 1.3.6.1.4.1.10106.2.1.1.359901.3
		hae3000c01v1DeemFailBTrap NOTIFICATION-TYPE
		OBJECTS { trapCounter, hae3000c01v1Index, hae3000c01v1DeemFailB }
		STATUS current
		DESCRIPTION
			"There is no valid deembedded audio Trap"
		::= { hae3000c01v1Traps 163 }

		-- 1.3.6.1.4.1.10106.2.1.1.359901.3
		hae3000c01v1DeemOvlBTrap NOTIFICATION-TYPE
		OBJECTS { trapCounter, hae3000c01v1Index, hae3000c01v1DeemOvlB }
		STATUS current
		DESCRIPTION
			"There is overload or silence in embed audio Trap"
		::= { hae3000c01v1Traps 165 }

		-- 1.3.6.1.4.1.10106.2.1.1.359901.3
		hae3000c01v1ClippingBTrap NOTIFICATION-TYPE
		OBJECTS { trapCounter, hae3000c01v1Index, hae3000c01v1ClippingB }
		STATUS current
		DESCRIPTION
			"Analog input clipping Trap"
		::= { hae3000c01v1Traps 167 }

		-- 1.3.6.1.4.1.10106.2.1.1.360001
		had3000c01v1Traps OBJECT IDENTIFIER ::= { albalaTraps 360001 }

		-- 1.3.6.1.4.1.10106.2.1.1.360001.3
		had3000c01v1NoSignalATrap NOTIFICATION-TYPE
		OBJECTS { trapCounter, had3000c01v1Index, had3000c01v1NoSignalA }
		STATUS current
		DESCRIPTION
			"There is no SDI signal or the format is not supported Trap"
		::= { had3000c01v1Traps 163 }

		-- 1.3.6.1.4.1.10106.2.1.1.360001.3
		had3000c01v1UnlockATrap NOTIFICATION-TYPE
		OBJECTS { trapCounter, had3000c01v1Index, had3000c01v1UnlockA }
		STATUS current
		DESCRIPTION
			"Indicates signal unlock fail Trap"
		::= { had3000c01v1Traps 165 }

		-- 1.3.6.1.4.1.10106.2.1.1.360001.3
		had3000c01v1EdhErrorATrap NOTIFICATION-TYPE
		OBJECTS { trapCounter, had3000c01v1Index, had3000c01v1EdhErrorA }
		STATUS current
		DESCRIPTION
			"There are EDH/CRC errors on SDI signal Trap"
		::= { had3000c01v1Traps 167 }

		-- 1.3.6.1.4.1.10106.2.1.1.360001.3
		had3000c01v1SampRFailATrap NOTIFICATION-TYPE
		OBJECTS { trapCounter, had3000c01v1Index, had3000c01v1SampRFailA }
		STATUS current
		DESCRIPTION
			"Indicates sampling rate fail Trap"
		::= { had3000c01v1Traps 169 }

		-- 1.3.6.1.4.1.10106.2.1.1.360001.3
		had3000c01v1DeemFailATrap NOTIFICATION-TYPE
		OBJECTS { trapCounter, had3000c01v1Index, had3000c01v1DeemFailA }
		STATUS current
		DESCRIPTION
			"There is no valid deembedded audio Trap"
		::= { had3000c01v1Traps 171 }

		-- 1.3.6.1.4.1.10106.2.1.1.360001.3
		had3000c01v1AesOvlATrap NOTIFICATION-TYPE
		OBJECTS { trapCounter, had3000c01v1Index, had3000c01v1AesOvlA }
		STATUS current
		DESCRIPTION
			"There is overload or silence in analog outputs Trap"
		::= { had3000c01v1Traps 173 }

		-- 1.3.6.1.4.1.10106.2.1.1.360001.3
		had3000c01v1DeemOvlATrap NOTIFICATION-TYPE
		OBJECTS { trapCounter, had3000c01v1Index, had3000c01v1DeemOvlA }
		STATUS current
		DESCRIPTION
			"There is overload or silence in embed audio Trap"
		::= { had3000c01v1Traps 175 }

		-- 1.3.6.1.4.1.10106.2.1.1.360001.3
		had3000c01v1NoSignalBTrap NOTIFICATION-TYPE
		OBJECTS { trapCounter, had3000c01v1Index, had3000c01v1NoSignalB }
		STATUS current
		DESCRIPTION
			"There is no SDI signal or the format is not supported Trap"
		::= { had3000c01v1Traps 179 }

		-- 1.3.6.1.4.1.10106.2.1.1.360001.3
		had3000c01v1UnlockBTrap NOTIFICATION-TYPE
		OBJECTS { trapCounter, had3000c01v1Index, had3000c01v1UnlockB }
		STATUS current
		DESCRIPTION
			"Indicates signal unlock fail Trap"
		::= { had3000c01v1Traps 181 }

		-- 1.3.6.1.4.1.10106.2.1.1.360001.3
		had3000c01v1EdhErrorBTrap NOTIFICATION-TYPE
		OBJECTS { trapCounter, had3000c01v1Index, had3000c01v1EdhErrorB }
		STATUS current
		DESCRIPTION
			"There are EDH/CRC errors on SDI signal Trap"
		::= { had3000c01v1Traps 183 }

		-- 1.3.6.1.4.1.10106.2.1.1.360001.3
		had3000c01v1SampRFailBTrap NOTIFICATION-TYPE
		OBJECTS { trapCounter, had3000c01v1Index, had3000c01v1SampRFailB }
		STATUS current
		DESCRIPTION
			"Indicates sampling rate fail Trap"
		::= { had3000c01v1Traps 185 }

		-- 1.3.6.1.4.1.10106.2.1.1.360001.3
		had3000c01v1DeemFailBTrap NOTIFICATION-TYPE
		OBJECTS { trapCounter, had3000c01v1Index, had3000c01v1DeemFailB }
		STATUS current
		DESCRIPTION
			"There is no valid deembedded audio Trap"
		::= { had3000c01v1Traps 187 }

		-- 1.3.6.1.4.1.10106.2.1.1.360001.3
		had3000c01v1AesOvlBTrap NOTIFICATION-TYPE
		OBJECTS { trapCounter, had3000c01v1Index, had3000c01v1AesOvlB }
		STATUS current
		DESCRIPTION
			"There is overload or silence in analog outputs Trap"
		::= { had3000c01v1Traps 189 }

		-- 1.3.6.1.4.1.10106.2.1.1.360001.3
		had3000c01v1DeemOvlBTrap NOTIFICATION-TYPE
		OBJECTS { trapCounter, had3000c01v1Index, had3000c01v1DeemOvlB }
		STATUS current
		DESCRIPTION
			"There is overload or silence in embed audio Trap"
		::= { had3000c01v1Traps 191 }

		-- 1.3.6.1.4.1.10106.2.1.1.362001
		ipa3000c01v1Traps OBJECT IDENTIFIER ::= { albalaTraps 362001 }

		-- 1.3.6.1.4.1.10106.2.1.1.362001.3
		ipa3000c01v1ModeTrap NOTIFICATION-TYPE
		OBJECTS { trapCounter, ipa3000c01v1Index, ipa3000c01v1Mode }
		STATUS current
		DESCRIPTION
			"Allows selecting the switching mode Trap"
		::= { ipa3000c01v1Traps 3 }

		-- 1.3.6.1.4.1.10106.2.1.1.362001.3
		ipa3000c01v1DvbTModeTrap NOTIFICATION-TYPE
		OBJECTS { trapCounter, ipa3000c01v1Index, ipa3000c01v1DvbTMode }
		STATUS current
		DESCRIPTION
			"Selects DVB-T mode. Trap"
		::= { ipa3000c01v1Traps 5 }

		-- 1.3.6.1.4.1.10106.2.1.1.362001.3
		ipa3000c01v1InputTrap NOTIFICATION-TYPE
		OBJECTS { trapCounter, ipa3000c01v1Index, ipa3000c01v1Input }
		STATUS current
		DESCRIPTION
			"Selected input Trap"
		::= { ipa3000c01v1Traps 13 }

		-- 1.3.6.1.4.1.10106.2.1.1.362001.3
		ipa3000c01v1OutDelayTrap NOTIFICATION-TYPE
		OBJECTS { trapCounter, ipa3000c01v1Index, ipa3000c01v1OutDelay }
		STATUS current
		DESCRIPTION
			"Output delay refered to 1PPS reference in DVB-T mode Trap"
		::= { ipa3000c01v1Traps 27 }

		-- 1.3.6.1.4.1.10106.2.1.1.362001.3
		ipa3000c01v11ppsFailTrap NOTIFICATION-TYPE
		OBJECTS { trapCounter, ipa3000c01v1Index, ipa3000c01v11ppsFail }
		STATUS current
		DESCRIPTION
			"1PPS reference input status Trap"
		::= { ipa3000c01v1Traps 195 }

		-- 1.3.6.1.4.1.10106.2.1.1.362001.3
		ipa3000c01v110mhzFailTrap NOTIFICATION-TYPE
		OBJECTS { trapCounter, ipa3000c01v1Index, ipa3000c01v110mhzFail }
		STATUS current
		DESCRIPTION
			"10MHz reference input status Trap"
		::= { ipa3000c01v1Traps 197 }

		-- 1.3.6.1.4.1.10106.2.1.1.362001.3
		ipa3000c01v1OutputFailTrap NOTIFICATION-TYPE
		OBJECTS { trapCounter, ipa3000c01v1Index, ipa3000c01v1OutputFail }
		STATUS current
		DESCRIPTION
			"The output signal is not valid because all inputs failed Trap"
		::= { ipa3000c01v1Traps 199 }

		-- 1.3.6.1.4.1.10106.2.1.1.362001.3
		ipa3000c01v1AsiMainDelWarTrap NOTIFICATION-TYPE
		OBJECTS { trapCounter, ipa3000c01v1Index, ipa3000c01v1AsiMainDelWar }
		STATUS current
		DESCRIPTION
			"The ASI main delay is greater than the programmed output delay Trap"
		::= { ipa3000c01v1Traps 201 }

		-- 1.3.6.1.4.1.10106.2.1.1.362001.3
		ipa3000c01v1AsiResDelWarTrap NOTIFICATION-TYPE
		OBJECTS { trapCounter, ipa3000c01v1Index, ipa3000c01v1AsiResDelWar }
		STATUS current
		DESCRIPTION
			"The ASI reserve delay is greater than the programmed output delay Trap"
		::= { ipa3000c01v1Traps 203 }

		-- 1.3.6.1.4.1.10106.2.1.1.362001.3
		ipa3000c01v1IpMainDelWarTrap NOTIFICATION-TYPE
		OBJECTS { trapCounter, ipa3000c01v1Index, ipa3000c01v1IpMainDelWar }
		STATUS current
		DESCRIPTION
			"The IP main delay is greater than the programmed output delay Trap"
		::= { ipa3000c01v1Traps 205 }

		-- 1.3.6.1.4.1.10106.2.1.1.362001.3
		ipa3000c01v1IpResDelWarTrap NOTIFICATION-TYPE
		OBJECTS { trapCounter, ipa3000c01v1Index, ipa3000c01v1IpResDelWar }
		STATUS current
		DESCRIPTION
			"The IP reserve delay is greater than the programmed output delay Trap"
		::= { ipa3000c01v1Traps 207 }

		-- 1.3.6.1.4.1.10106.2.1.1.362001.3
		ipa3000c01v1AsiMainFailTrap NOTIFICATION-TYPE
		OBJECTS { trapCounter, ipa3000c01v1Index, ipa3000c01v1AsiMainFail }
		STATUS current
		DESCRIPTION
			"ASI main input status Trap"
		::= { ipa3000c01v1Traps 209 }

		-- 1.3.6.1.4.1.10106.2.1.1.362001.3
		ipa3000c01v1ExAsiMainFailTrap NOTIFICATION-TYPE
		OBJECTS { trapCounter, ipa3000c01v1Index, ipa3000c01v1ExAsiMainFail }
		STATUS current
		DESCRIPTION
			"ASI main external input fail status Trap"
		::= { ipa3000c01v1Traps 211 }

		-- 1.3.6.1.4.1.10106.2.1.1.362001.3
		ipa3000c01v1AsiResFailTrap NOTIFICATION-TYPE
		OBJECTS { trapCounter, ipa3000c01v1Index, ipa3000c01v1AsiResFail }
		STATUS current
		DESCRIPTION
			"ASI reserve input status Trap"
		::= { ipa3000c01v1Traps 213 }

		-- 1.3.6.1.4.1.10106.2.1.1.362001.3
		ipa3000c01v1ExAsiResFailTrap NOTIFICATION-TYPE
		OBJECTS { trapCounter, ipa3000c01v1Index, ipa3000c01v1ExAsiResFail }
		STATUS current
		DESCRIPTION
			"ASI reserve external input fail status Trap"
		::= { ipa3000c01v1Traps 215 }

		-- 1.3.6.1.4.1.10106.2.1.1.362001.3
		ipa3000c01v1IpMainFailTrap NOTIFICATION-TYPE
		OBJECTS { trapCounter, ipa3000c01v1Index, ipa3000c01v1IpMainFail }
		STATUS current
		DESCRIPTION
			"IP main input status Trap"
		::= { ipa3000c01v1Traps 217 }

		-- 1.3.6.1.4.1.10106.2.1.1.362001.3
		ipa3000c01v1ExIpMainFailTrap NOTIFICATION-TYPE
		OBJECTS { trapCounter, ipa3000c01v1Index, ipa3000c01v1ExIpMainFail }
		STATUS current
		DESCRIPTION
			"IP main external input fail status Trap"
		::= { ipa3000c01v1Traps 219 }

		-- 1.3.6.1.4.1.10106.2.1.1.362001.3
		ipa3000c01v1IpResFailTrap NOTIFICATION-TYPE
		OBJECTS { trapCounter, ipa3000c01v1Index, ipa3000c01v1IpResFail }
		STATUS current
		DESCRIPTION
			"IP reserve input status Trap"
		::= { ipa3000c01v1Traps 221 }

		-- 1.3.6.1.4.1.10106.2.1.1.362001.3
		ipa3000c01v1ExIpResFailTrap NOTIFICATION-TYPE
		OBJECTS { trapCounter, ipa3000c01v1Index, ipa3000c01v1ExIpResFail }
		STATUS current
		DESCRIPTION
			"IP reserve external input fail status Trap"
		::= { ipa3000c01v1Traps 223 }

		-- 1.3.6.1.4.1.10106.2.1.1.362001.3
		ipa3000c01v1GlobalSeamTrap NOTIFICATION-TYPE
		OBJECTS { trapCounter, ipa3000c01v1Index, ipa3000c01v1GlobalSeam }
		STATUS current
		DESCRIPTION
			"Global seamles switching capability Trap"
		::= { ipa3000c01v1Traps 237 }

		-- 1.3.6.1.4.1.10106.2.1.1.362002
		ipa3000c01v2Traps OBJECT IDENTIFIER ::= { albalaTraps 362002 }

		-- 1.3.6.1.4.1.10106.2.1.1.362002.3
		ipa3000c01v2ModeTrap NOTIFICATION-TYPE
		OBJECTS { trapCounter, ipa3000c01v2Index, ipa3000c01v2Mode }
		STATUS current
		DESCRIPTION
			"Allows selecting the switching mode Trap"
		::= { ipa3000c01v2Traps 3 }

		-- 1.3.6.1.4.1.10106.2.1.1.362002.3
		ipa3000c01v2DvbTModeTrap NOTIFICATION-TYPE
		OBJECTS { trapCounter, ipa3000c01v2Index, ipa3000c01v2DvbTMode }
		STATUS current
		DESCRIPTION
			"Selects DVB-T mode. Trap"
		::= { ipa3000c01v2Traps 5 }

		-- 1.3.6.1.4.1.10106.2.1.1.362002.3
		ipa3000c01v2InputTrap NOTIFICATION-TYPE
		OBJECTS { trapCounter, ipa3000c01v2Index, ipa3000c01v2Input }
		STATUS current
		DESCRIPTION
			"Selected input Trap"
		::= { ipa3000c01v2Traps 17 }

		-- 1.3.6.1.4.1.10106.2.1.1.362002.3
		ipa3000c01v2OutDelayTrap NOTIFICATION-TYPE
		OBJECTS { trapCounter, ipa3000c01v2Index, ipa3000c01v2OutDelay }
		STATUS current
		DESCRIPTION
			"Output delay refered to 1PPS reference in DVB-T mode Trap"
		::= { ipa3000c01v2Traps 31 }

		-- 1.3.6.1.4.1.10106.2.1.1.362002.3
		ipa3000c01v21ppsFailTrap NOTIFICATION-TYPE
		OBJECTS { trapCounter, ipa3000c01v2Index, ipa3000c01v21ppsFail }
		STATUS current
		DESCRIPTION
			"1PPS reference input status Trap"
		::= { ipa3000c01v2Traps 221 }

		-- 1.3.6.1.4.1.10106.2.1.1.362002.3
		ipa3000c01v210mhzFailTrap NOTIFICATION-TYPE
		OBJECTS { trapCounter, ipa3000c01v2Index, ipa3000c01v210mhzFail }
		STATUS current
		DESCRIPTION
			"10MHz reference input status Trap"
		::= { ipa3000c01v2Traps 223 }

		-- 1.3.6.1.4.1.10106.2.1.1.362002.3
		ipa3000c01v2OutputFailTrap NOTIFICATION-TYPE
		OBJECTS { trapCounter, ipa3000c01v2Index, ipa3000c01v2OutputFail }
		STATUS current
		DESCRIPTION
			"The output signal is not valid because all inputs failed Trap"
		::= { ipa3000c01v2Traps 225 }

		-- 1.3.6.1.4.1.10106.2.1.1.362002.3
		ipa3000c01v2AsiMainDelWarTrap NOTIFICATION-TYPE
		OBJECTS { trapCounter, ipa3000c01v2Index, ipa3000c01v2AsiMainDelWar }
		STATUS current
		DESCRIPTION
			"The ASI main delay is greater than the programmed output delay Trap"
		::= { ipa3000c01v2Traps 227 }

		-- 1.3.6.1.4.1.10106.2.1.1.362002.3
		ipa3000c01v2AsiResDelWarTrap NOTIFICATION-TYPE
		OBJECTS { trapCounter, ipa3000c01v2Index, ipa3000c01v2AsiResDelWar }
		STATUS current
		DESCRIPTION
			"The ASI reserve delay is greater than the programmed output delay Trap"
		::= { ipa3000c01v2Traps 229 }

		-- 1.3.6.1.4.1.10106.2.1.1.362002.3
		ipa3000c01v2IpMainDelWarTrap NOTIFICATION-TYPE
		OBJECTS { trapCounter, ipa3000c01v2Index, ipa3000c01v2IpMainDelWar }
		STATUS current
		DESCRIPTION
			"The IP main delay is greater than the programmed output delay Trap"
		::= { ipa3000c01v2Traps 231 }

		-- 1.3.6.1.4.1.10106.2.1.1.362002.3
		ipa3000c01v2IpResDelWarTrap NOTIFICATION-TYPE
		OBJECTS { trapCounter, ipa3000c01v2Index, ipa3000c01v2IpResDelWar }
		STATUS current
		DESCRIPTION
			"The IP reserve delay is greater than the programmed output delay Trap"
		::= { ipa3000c01v2Traps 233 }

		-- 1.3.6.1.4.1.10106.2.1.1.362002.3
		ipa3000c01v2AsiMainFailTrap NOTIFICATION-TYPE
		OBJECTS { trapCounter, ipa3000c01v2Index, ipa3000c01v2AsiMainFail }
		STATUS current
		DESCRIPTION
			"ASI main input status Trap"
		::= { ipa3000c01v2Traps 235 }

		-- 1.3.6.1.4.1.10106.2.1.1.362002.3
		ipa3000c01v2ExAsiMainFailTrap NOTIFICATION-TYPE
		OBJECTS { trapCounter, ipa3000c01v2Index, ipa3000c01v2ExAsiMainFail }
		STATUS current
		DESCRIPTION
			"ASI main external input fail status Trap"
		::= { ipa3000c01v2Traps 237 }

		-- 1.3.6.1.4.1.10106.2.1.1.362002.3
		ipa3000c01v2AsiResFailTrap NOTIFICATION-TYPE
		OBJECTS { trapCounter, ipa3000c01v2Index, ipa3000c01v2AsiResFail }
		STATUS current
		DESCRIPTION
			"ASI reserve input status Trap"
		::= { ipa3000c01v2Traps 239 }

		-- 1.3.6.1.4.1.10106.2.1.1.362002.3
		ipa3000c01v2ExAsiResFailTrap NOTIFICATION-TYPE
		OBJECTS { trapCounter, ipa3000c01v2Index, ipa3000c01v2ExAsiResFail }
		STATUS current
		DESCRIPTION
			"ASI reserve external input fail status Trap"
		::= { ipa3000c01v2Traps 241 }

		-- 1.3.6.1.4.1.10106.2.1.1.362002.3
		ipa3000c01v2IpMainFailTrap NOTIFICATION-TYPE
		OBJECTS { trapCounter, ipa3000c01v2Index, ipa3000c01v2IpMainFail }
		STATUS current
		DESCRIPTION
			"IP main input status Trap"
		::= { ipa3000c01v2Traps 243 }

		-- 1.3.6.1.4.1.10106.2.1.1.362002.3
		ipa3000c01v2ExIpMainFailTrap NOTIFICATION-TYPE
		OBJECTS { trapCounter, ipa3000c01v2Index, ipa3000c01v2ExIpMainFail }
		STATUS current
		DESCRIPTION
			"IP main external input fail status Trap"
		::= { ipa3000c01v2Traps 245 }

		-- 1.3.6.1.4.1.10106.2.1.1.362002.3
		ipa3000c01v2IpResFailTrap NOTIFICATION-TYPE
		OBJECTS { trapCounter, ipa3000c01v2Index, ipa3000c01v2IpResFail }
		STATUS current
		DESCRIPTION
			"IP reserve input status Trap"
		::= { ipa3000c01v2Traps 247 }

		-- 1.3.6.1.4.1.10106.2.1.1.362002.3
		ipa3000c01v2ExIpResFailTrap NOTIFICATION-TYPE
		OBJECTS { trapCounter, ipa3000c01v2Index, ipa3000c01v2ExIpResFail }
		STATUS current
		DESCRIPTION
			"IP reserve external input fail status Trap"
		::= { ipa3000c01v2Traps 249 }

		-- 1.3.6.1.4.1.10106.2.1.1.362002.3
		ipa3000c01v2GlobalSeamTrap NOTIFICATION-TYPE
		OBJECTS { trapCounter, ipa3000c01v2Index, ipa3000c01v2GlobalSeam }
		STATUS current
		DESCRIPTION
			"Global seamles switching capability Trap"
		::= { ipa3000c01v2Traps 263 }

		-- 1.3.6.1.4.1.10106.2.1.1.364801
		hsw3000c01v1Traps OBJECT IDENTIFIER ::= { albalaTraps 364801 }

		-- 1.3.6.1.4.1.10106.2.1.1.364801.3
		hsw3000c01v1StateSelTrap NOTIFICATION-TYPE
		OBJECTS { trapCounter, hsw3000c01v1Index, hsw3000c01v1StateSel }
		STATUS current
		DESCRIPTION
			"Shows the module's current state Trap"
		::= { hsw3000c01v1Traps 9 }

		-- 1.3.6.1.4.1.10106.2.1.1.364801.3
		hsw3000c01v1SwitchModeTrap NOTIFICATION-TYPE
		OBJECTS { trapCounter, hsw3000c01v1Index, hsw3000c01v1SwitchMode }
		STATUS current
		DESCRIPTION
			"Allows selecting the switching mode Trap"
		::= { hsw3000c01v1Traps 11 }

		-- 1.3.6.1.4.1.10106.2.1.1.364801.3
		hsw3000c01v1BypassEnableTrap NOTIFICATION-TYPE
		OBJECTS { trapCounter, hsw3000c01v1Index, hsw3000c01v1BypassEnable }
		STATUS current
		DESCRIPTION
			"Allows activating the rear board bypass Trap"
		::= { hsw3000c01v1Traps 15 }

		-- 1.3.6.1.4.1.10106.2.1.1.364801.3
		hsw3000c01v1OperatingModeTrap NOTIFICATION-TYPE
		OBJECTS { trapCounter, hsw3000c01v1Index, hsw3000c01v1OperatingMode }
		STATUS current
		DESCRIPTION
			"Allows selecting the operating mode Trap"
		::= { hsw3000c01v1Traps 19 }

		-- 1.3.6.1.4.1.10106.2.1.1.364801.3
		hsw3000c01v1In1FailTrap NOTIFICATION-TYPE
		OBJECTS { trapCounter, hsw3000c01v1Index, hsw3000c01v1In1Fail }
		STATUS current
		DESCRIPTION
			"Input 1 fail Trap"
		::= { hsw3000c01v1Traps 115 }

		-- 1.3.6.1.4.1.10106.2.1.1.364801.3
		hsw3000c01v1In2FailTrap NOTIFICATION-TYPE
		OBJECTS { trapCounter, hsw3000c01v1Index, hsw3000c01v1In2Fail }
		STATUS current
		DESCRIPTION
			"Input 2 fail Trap"
		::= { hsw3000c01v1Traps 117 }

		-- 1.3.6.1.4.1.10106.2.1.1.364801.3
		hsw3000c01v1In1ExtFailTrap NOTIFICATION-TYPE
		OBJECTS { trapCounter, hsw3000c01v1Index, hsw3000c01v1In1ExtFail }
		STATUS current
		DESCRIPTION
			"Input 1 GPI fail (GPI1A) Trap"
		::= { hsw3000c01v1Traps 119 }

		-- 1.3.6.1.4.1.10106.2.1.1.364801.3
		hsw3000c01v1In2ExtFailTrap NOTIFICATION-TYPE
		OBJECTS { trapCounter, hsw3000c01v1Index, hsw3000c01v1In2ExtFail }
		STATUS current
		DESCRIPTION
			"Input 2 GPI fail (GPI2A) Trap"
		::= { hsw3000c01v1Traps 121 }

		-- 1.3.6.1.4.1.10106.2.1.1.364801.3
		hsw3000c01v1BlindExtFailTrap NOTIFICATION-TYPE
		OBJECTS { trapCounter, hsw3000c01v1Index, hsw3000c01v1BlindExtFail }
		STATUS current
		DESCRIPTION
			"Blind halfauto control GPI fail (GPI2B) Trap"
		::= { hsw3000c01v1Traps 123 }

		-- 1.3.6.1.4.1.10106.2.1.1.364801.3
		hsw3000c01v1SelOut1Trap NOTIFICATION-TYPE
		OBJECTS { trapCounter, hsw3000c01v1Index, hsw3000c01v1SelOut1 }
		STATUS current
		DESCRIPTION
			"Output 1 Trap"
		::= { hsw3000c01v1Traps 125 }

		-- 1.3.6.1.4.1.10106.2.1.1.364801.3
		hsw3000c01v1SelOut2Trap NOTIFICATION-TYPE
		OBJECTS { trapCounter, hsw3000c01v1Index, hsw3000c01v1SelOut2 }
		STATUS current
		DESCRIPTION
			"Output 2 Trap"
		::= { hsw3000c01v1Traps 127 }

		-- 1.3.6.1.4.1.10106.2.1.1.364801.3
		hsw3000c01v1Gpi3StatTrap NOTIFICATION-TYPE
		OBJECTS { trapCounter, hsw3000c01v1Index, hsw3000c01v1Gpi3Stat }
		STATUS current
		DESCRIPTION
			"GPI1B status (used in remote control) Trap"
		::= { hsw3000c01v1Traps 129 }

		-- 1.3.6.1.4.1.10106.2.1.1.364801.3
		hsw3000c01v1In1PhyFailTrap NOTIFICATION-TYPE
		OBJECTS { trapCounter, hsw3000c01v1Index, hsw3000c01v1In1PhyFail }
		STATUS current
		DESCRIPTION
			"Absence fail Trap"
		::= { hsw3000c01v1Traps 131 }

		-- 1.3.6.1.4.1.10106.2.1.1.364801.3
		hsw3000c01v1In1FmtFailTrap NOTIFICATION-TYPE
		OBJECTS { trapCounter, hsw3000c01v1Index, hsw3000c01v1In1FmtFail }
		STATUS current
		DESCRIPTION
			"Format fail Trap"
		::= { hsw3000c01v1Traps 133 }

		-- 1.3.6.1.4.1.10106.2.1.1.364801.3
		hsw3000c01v1In1IncFailTrap NOTIFICATION-TYPE
		OBJECTS { trapCounter, hsw3000c01v1Index, hsw3000c01v1In1IncFail }
		STATUS current
		DESCRIPTION
			"Incompatible format fail Trap"
		::= { hsw3000c01v1Traps 135 }

		-- 1.3.6.1.4.1.10106.2.1.1.364801.3
		hsw3000c01v1In1GpiFailTrap NOTIFICATION-TYPE
		OBJECTS { trapCounter, hsw3000c01v1Index, hsw3000c01v1In1GpiFail }
		STATUS current
		DESCRIPTION
			"External GPI fail Trap"
		::= { hsw3000c01v1Traps 137 }

		-- 1.3.6.1.4.1.10106.2.1.1.364801.3
		hsw3000c01v1In1BlkFailTrap NOTIFICATION-TYPE
		OBJECTS { trapCounter, hsw3000c01v1Index, hsw3000c01v1In1BlkFail }
		STATUS current
		DESCRIPTION
			"Black signal fail Trap"
		::= { hsw3000c01v1Traps 139 }

		-- 1.3.6.1.4.1.10106.2.1.1.364801.3
		hsw3000c01v1In1FrzFailTrap NOTIFICATION-TYPE
		OBJECTS { trapCounter, hsw3000c01v1Index, hsw3000c01v1In1FrzFail }
		STATUS current
		DESCRIPTION
			"Freeze signal fail Trap"
		::= { hsw3000c01v1Traps 141 }

		-- 1.3.6.1.4.1.10106.2.1.1.364801.3
		hsw3000c01v1In1PatFailTrap NOTIFICATION-TYPE
		OBJECTS { trapCounter, hsw3000c01v1Index, hsw3000c01v1In1PatFail }
		STATUS current
		DESCRIPTION
			"Video pattern fail Trap"
		::= { hsw3000c01v1Traps 143 }

		-- 1.3.6.1.4.1.10106.2.1.1.364801.3
		hsw3000c01v1In1CrcFailTrap NOTIFICATION-TYPE
		OBJECTS { trapCounter, hsw3000c01v1Index, hsw3000c01v1In1CrcFail }
		STATUS current
		DESCRIPTION
			"EDH/CRC fail Trap"
		::= { hsw3000c01v1Traps 145 }

		-- 1.3.6.1.4.1.10106.2.1.1.364801.3
		hsw3000c01v1In2PhyFailTrap NOTIFICATION-TYPE
		OBJECTS { trapCounter, hsw3000c01v1Index, hsw3000c01v1In2PhyFail }
		STATUS current
		DESCRIPTION
			"Absence fail Trap"
		::= { hsw3000c01v1Traps 147 }

		-- 1.3.6.1.4.1.10106.2.1.1.364801.3
		hsw3000c01v1In2FmtFailTrap NOTIFICATION-TYPE
		OBJECTS { trapCounter, hsw3000c01v1Index, hsw3000c01v1In2FmtFail }
		STATUS current
		DESCRIPTION
			"Format fail Trap"
		::= { hsw3000c01v1Traps 149 }

		-- 1.3.6.1.4.1.10106.2.1.1.364801.3
		hsw3000c01v1In2IncFailTrap NOTIFICATION-TYPE
		OBJECTS { trapCounter, hsw3000c01v1Index, hsw3000c01v1In2IncFail }
		STATUS current
		DESCRIPTION
			"Incompatible format fail Trap"
		::= { hsw3000c01v1Traps 151 }

		-- 1.3.6.1.4.1.10106.2.1.1.364801.3
		hsw3000c01v1In2GpiFailTrap NOTIFICATION-TYPE
		OBJECTS { trapCounter, hsw3000c01v1Index, hsw3000c01v1In2GpiFail }
		STATUS current
		DESCRIPTION
			"External GPI fail Trap"
		::= { hsw3000c01v1Traps 153 }

		-- 1.3.6.1.4.1.10106.2.1.1.364801.3
		hsw3000c01v1In2BlkFailTrap NOTIFICATION-TYPE
		OBJECTS { trapCounter, hsw3000c01v1Index, hsw3000c01v1In2BlkFail }
		STATUS current
		DESCRIPTION
			"Black signal fail Trap"
		::= { hsw3000c01v1Traps 155 }

		-- 1.3.6.1.4.1.10106.2.1.1.364801.3
		hsw3000c01v1In2FrzFailTrap NOTIFICATION-TYPE
		OBJECTS { trapCounter, hsw3000c01v1Index, hsw3000c01v1In2FrzFail }
		STATUS current
		DESCRIPTION
			"Freeze signal fail Trap"
		::= { hsw3000c01v1Traps 157 }

		-- 1.3.6.1.4.1.10106.2.1.1.364801.3
		hsw3000c01v1In2PatFailTrap NOTIFICATION-TYPE
		OBJECTS { trapCounter, hsw3000c01v1Index, hsw3000c01v1In2PatFail }
		STATUS current
		DESCRIPTION
			"Video pattern fail Trap"
		::= { hsw3000c01v1Traps 159 }

		-- 1.3.6.1.4.1.10106.2.1.1.364801.3
		hsw3000c01v1In2CrcFailTrap NOTIFICATION-TYPE
		OBJECTS { trapCounter, hsw3000c01v1Index, hsw3000c01v1In2CrcFail }
		STATUS current
		DESCRIPTION
			"EDH/CRC fail Trap"
		::= { hsw3000c01v1Traps 161 }

		-- 1.3.6.1.4.1.10106.2.1.1.364801.3
		hsw3000c01v1RefFailTrap NOTIFICATION-TYPE
		OBJECTS { trapCounter, hsw3000c01v1Index, hsw3000c01v1RefFail }
		STATUS current
		DESCRIPTION
			"Reference absence fail Trap"
		::= { hsw3000c01v1Traps 163 }

		-- 1.3.6.1.4.1.10106.2.1.1.364801.3
		hsw3000c01v1LockFailTrap NOTIFICATION-TYPE
		OBJECTS { trapCounter, hsw3000c01v1Index, hsw3000c01v1LockFail }
		STATUS current
		DESCRIPTION
			"Reference unlock fail Trap"
		::= { hsw3000c01v1Traps 165 }

		-- 1.3.6.1.4.1.10106.2.1.1.364802
		hsw3000c01v2Traps OBJECT IDENTIFIER ::= { albalaTraps 364802 }

		-- 1.3.6.1.4.1.10106.2.1.1.364802.3
		hsw3000c01v2StateSelTrap NOTIFICATION-TYPE
		OBJECTS { trapCounter, hsw3000c01v2Index, hsw3000c01v2StateSel }
		STATUS current
		DESCRIPTION
			"Shows the module's current state Trap"
		::= { hsw3000c01v2Traps 9 }

		-- 1.3.6.1.4.1.10106.2.1.1.364802.3
		hsw3000c01v2SwitchModeTrap NOTIFICATION-TYPE
		OBJECTS { trapCounter, hsw3000c01v2Index, hsw3000c01v2SwitchMode }
		STATUS current
		DESCRIPTION
			"Allows selecting the switching mode Trap"
		::= { hsw3000c01v2Traps 11 }

		-- 1.3.6.1.4.1.10106.2.1.1.364802.3
		hsw3000c01v2BypassEnableTrap NOTIFICATION-TYPE
		OBJECTS { trapCounter, hsw3000c01v2Index, hsw3000c01v2BypassEnable }
		STATUS current
		DESCRIPTION
			"Allows activating the rear board bypass Trap"
		::= { hsw3000c01v2Traps 15 }

		-- 1.3.6.1.4.1.10106.2.1.1.364802.3
		hsw3000c01v2OperatingModeTrap NOTIFICATION-TYPE
		OBJECTS { trapCounter, hsw3000c01v2Index, hsw3000c01v2OperatingMode }
		STATUS current
		DESCRIPTION
			"Allows selecting the operating mode Trap"
		::= { hsw3000c01v2Traps 19 }

		-- 1.3.6.1.4.1.10106.2.1.1.364802.3
		hsw3000c01v2In1FailTrap NOTIFICATION-TYPE
		OBJECTS { trapCounter, hsw3000c01v2Index, hsw3000c01v2In1Fail }
		STATUS current
		DESCRIPTION
			"Input 1 fail Trap"
		::= { hsw3000c01v2Traps 179 }

		-- 1.3.6.1.4.1.10106.2.1.1.364802.3
		hsw3000c01v2In2FailTrap NOTIFICATION-TYPE
		OBJECTS { trapCounter, hsw3000c01v2Index, hsw3000c01v2In2Fail }
		STATUS current
		DESCRIPTION
			"Input 2 fail Trap"
		::= { hsw3000c01v2Traps 181 }

		-- 1.3.6.1.4.1.10106.2.1.1.364802.3
		hsw3000c01v2In1ExtFailTrap NOTIFICATION-TYPE
		OBJECTS { trapCounter, hsw3000c01v2Index, hsw3000c01v2In1ExtFail }
		STATUS current
		DESCRIPTION
			"Input 1 GPI fail (GPI1A) Trap"
		::= { hsw3000c01v2Traps 183 }

		-- 1.3.6.1.4.1.10106.2.1.1.364802.3
		hsw3000c01v2In2ExtFailTrap NOTIFICATION-TYPE
		OBJECTS { trapCounter, hsw3000c01v2Index, hsw3000c01v2In2ExtFail }
		STATUS current
		DESCRIPTION
			"Input 2 GPI fail (GPI2A) Trap"
		::= { hsw3000c01v2Traps 185 }

		-- 1.3.6.1.4.1.10106.2.1.1.364802.3
		hsw3000c01v2BlindExtFailTrap NOTIFICATION-TYPE
		OBJECTS { trapCounter, hsw3000c01v2Index, hsw3000c01v2BlindExtFail }
		STATUS current
		DESCRIPTION
			"Blind halfauto control GPI fail (GPI2B) Trap"
		::= { hsw3000c01v2Traps 187 }

		-- 1.3.6.1.4.1.10106.2.1.1.364802.3
		hsw3000c01v2SelOut1Trap NOTIFICATION-TYPE
		OBJECTS { trapCounter, hsw3000c01v2Index, hsw3000c01v2SelOut1 }
		STATUS current
		DESCRIPTION
			"Output 1 Trap"
		::= { hsw3000c01v2Traps 189 }

		-- 1.3.6.1.4.1.10106.2.1.1.364802.3
		hsw3000c01v2SelOut2Trap NOTIFICATION-TYPE
		OBJECTS { trapCounter, hsw3000c01v2Index, hsw3000c01v2SelOut2 }
		STATUS current
		DESCRIPTION
			"Output 2 Trap"
		::= { hsw3000c01v2Traps 191 }

		-- 1.3.6.1.4.1.10106.2.1.1.364802.3
		hsw3000c01v2Gpi3StatTrap NOTIFICATION-TYPE
		OBJECTS { trapCounter, hsw3000c01v2Index, hsw3000c01v2Gpi3Stat }
		STATUS current
		DESCRIPTION
			"GPI1B status (used in remote control) Trap"
		::= { hsw3000c01v2Traps 193 }

		-- 1.3.6.1.4.1.10106.2.1.1.364802.3
		hsw3000c01v2In1PhyFailTrap NOTIFICATION-TYPE
		OBJECTS { trapCounter, hsw3000c01v2Index, hsw3000c01v2In1PhyFail }
		STATUS current
		DESCRIPTION
			"Absence fail Trap"
		::= { hsw3000c01v2Traps 195 }

		-- 1.3.6.1.4.1.10106.2.1.1.364802.3
		hsw3000c01v2In1FmtFailTrap NOTIFICATION-TYPE
		OBJECTS { trapCounter, hsw3000c01v2Index, hsw3000c01v2In1FmtFail }
		STATUS current
		DESCRIPTION
			"Format fail Trap"
		::= { hsw3000c01v2Traps 197 }

		-- 1.3.6.1.4.1.10106.2.1.1.364802.3
		hsw3000c01v2In1IncFailTrap NOTIFICATION-TYPE
		OBJECTS { trapCounter, hsw3000c01v2Index, hsw3000c01v2In1IncFail }
		STATUS current
		DESCRIPTION
			"Incompatible format fail Trap"
		::= { hsw3000c01v2Traps 199 }

		-- 1.3.6.1.4.1.10106.2.1.1.364802.3
		hsw3000c01v2In1GpiFailTrap NOTIFICATION-TYPE
		OBJECTS { trapCounter, hsw3000c01v2Index, hsw3000c01v2In1GpiFail }
		STATUS current
		DESCRIPTION
			"External GPI fail Trap"
		::= { hsw3000c01v2Traps 201 }

		-- 1.3.6.1.4.1.10106.2.1.1.364802.3
		hsw3000c01v2In1BlkFailTrap NOTIFICATION-TYPE
		OBJECTS { trapCounter, hsw3000c01v2Index, hsw3000c01v2In1BlkFail }
		STATUS current
		DESCRIPTION
			"Black signal fail Trap"
		::= { hsw3000c01v2Traps 203 }

		-- 1.3.6.1.4.1.10106.2.1.1.364802.3
		hsw3000c01v2In1FrzFailTrap NOTIFICATION-TYPE
		OBJECTS { trapCounter, hsw3000c01v2Index, hsw3000c01v2In1FrzFail }
		STATUS current
		DESCRIPTION
			"Freeze signal fail Trap"
		::= { hsw3000c01v2Traps 205 }

		-- 1.3.6.1.4.1.10106.2.1.1.364802.3
		hsw3000c01v2In1PatFailTrap NOTIFICATION-TYPE
		OBJECTS { trapCounter, hsw3000c01v2Index, hsw3000c01v2In1PatFail }
		STATUS current
		DESCRIPTION
			"Video pattern fail Trap"
		::= { hsw3000c01v2Traps 207 }

		-- 1.3.6.1.4.1.10106.2.1.1.364802.3
		hsw3000c01v2In1CrcFailTrap NOTIFICATION-TYPE
		OBJECTS { trapCounter, hsw3000c01v2Index, hsw3000c01v2In1CrcFail }
		STATUS current
		DESCRIPTION
			"EDH/CRC fail Trap"
		::= { hsw3000c01v2Traps 209 }

		-- 1.3.6.1.4.1.10106.2.1.1.364802.3
		hsw3000c01v2In1SilFailTrap NOTIFICATION-TYPE
		OBJECTS { trapCounter, hsw3000c01v2Index, hsw3000c01v2In1SilFail }
		STATUS current
		DESCRIPTION
			"Audio silence fail Trap"
		::= { hsw3000c01v2Traps 211 }

		-- 1.3.6.1.4.1.10106.2.1.1.364802.3
		hsw3000c01v2In1OvrFailTrap NOTIFICATION-TYPE
		OBJECTS { trapCounter, hsw3000c01v2Index, hsw3000c01v2In1OvrFail }
		STATUS current
		DESCRIPTION
			"Audio overload fail Trap"
		::= { hsw3000c01v2Traps 213 }

		-- 1.3.6.1.4.1.10106.2.1.1.364802.3
		hsw3000c01v2In1PhFailTrap NOTIFICATION-TYPE
		OBJECTS { trapCounter, hsw3000c01v2Index, hsw3000c01v2In1PhFail }
		STATUS current
		DESCRIPTION
			"Audio phase fail Trap"
		::= { hsw3000c01v2Traps 215 }

		-- 1.3.6.1.4.1.10106.2.1.1.364802.3
		hsw3000c01v2In1PreFailTrap NOTIFICATION-TYPE
		OBJECTS { trapCounter, hsw3000c01v2Index, hsw3000c01v2In1PreFail }
		STATUS current
		DESCRIPTION
			"Audio presence fail Trap"
		::= { hsw3000c01v2Traps 217 }

		-- 1.3.6.1.4.1.10106.2.1.1.364802.3
		hsw3000c01v2In2PhyFailTrap NOTIFICATION-TYPE
		OBJECTS { trapCounter, hsw3000c01v2Index, hsw3000c01v2In2PhyFail }
		STATUS current
		DESCRIPTION
			"Absence fail Trap"
		::= { hsw3000c01v2Traps 219 }

		-- 1.3.6.1.4.1.10106.2.1.1.364802.3
		hsw3000c01v2In2FmtFailTrap NOTIFICATION-TYPE
		OBJECTS { trapCounter, hsw3000c01v2Index, hsw3000c01v2In2FmtFail }
		STATUS current
		DESCRIPTION
			"Format fail Trap"
		::= { hsw3000c01v2Traps 221 }

		-- 1.3.6.1.4.1.10106.2.1.1.364802.3
		hsw3000c01v2In2IncFailTrap NOTIFICATION-TYPE
		OBJECTS { trapCounter, hsw3000c01v2Index, hsw3000c01v2In2IncFail }
		STATUS current
		DESCRIPTION
			"Incompatible format fail Trap"
		::= { hsw3000c01v2Traps 223 }

		-- 1.3.6.1.4.1.10106.2.1.1.364802.3
		hsw3000c01v2In2GpiFailTrap NOTIFICATION-TYPE
		OBJECTS { trapCounter, hsw3000c01v2Index, hsw3000c01v2In2GpiFail }
		STATUS current
		DESCRIPTION
			"External GPI fail Trap"
		::= { hsw3000c01v2Traps 225 }

		-- 1.3.6.1.4.1.10106.2.1.1.364802.3
		hsw3000c01v2In2BlkFailTrap NOTIFICATION-TYPE
		OBJECTS { trapCounter, hsw3000c01v2Index, hsw3000c01v2In2BlkFail }
		STATUS current
		DESCRIPTION
			"Black signal fail Trap"
		::= { hsw3000c01v2Traps 227 }

		-- 1.3.6.1.4.1.10106.2.1.1.364802.3
		hsw3000c01v2In2FrzFailTrap NOTIFICATION-TYPE
		OBJECTS { trapCounter, hsw3000c01v2Index, hsw3000c01v2In2FrzFail }
		STATUS current
		DESCRIPTION
			"Freeze signal fail Trap"
		::= { hsw3000c01v2Traps 229 }

		-- 1.3.6.1.4.1.10106.2.1.1.364802.3
		hsw3000c01v2In2PatFailTrap NOTIFICATION-TYPE
		OBJECTS { trapCounter, hsw3000c01v2Index, hsw3000c01v2In2PatFail }
		STATUS current
		DESCRIPTION
			"Video pattern fail Trap"
		::= { hsw3000c01v2Traps 231 }

		-- 1.3.6.1.4.1.10106.2.1.1.364802.3
		hsw3000c01v2In2CrcFailTrap NOTIFICATION-TYPE
		OBJECTS { trapCounter, hsw3000c01v2Index, hsw3000c01v2In2CrcFail }
		STATUS current
		DESCRIPTION
			"EDH/CRC fail Trap"
		::= { hsw3000c01v2Traps 233 }

		-- 1.3.6.1.4.1.10106.2.1.1.364802.3
		hsw3000c01v2In2SilFailTrap NOTIFICATION-TYPE
		OBJECTS { trapCounter, hsw3000c01v2Index, hsw3000c01v2In2SilFail }
		STATUS current
		DESCRIPTION
			"Audio silence fail Trap"
		::= { hsw3000c01v2Traps 235 }

		-- 1.3.6.1.4.1.10106.2.1.1.364802.3
		hsw3000c01v2In2OvrFailTrap NOTIFICATION-TYPE
		OBJECTS { trapCounter, hsw3000c01v2Index, hsw3000c01v2In2OvrFail }
		STATUS current
		DESCRIPTION
			"Audio overload fail Trap"
		::= { hsw3000c01v2Traps 237 }

		-- 1.3.6.1.4.1.10106.2.1.1.364802.3
		hsw3000c01v2In2PhFailTrap NOTIFICATION-TYPE
		OBJECTS { trapCounter, hsw3000c01v2Index, hsw3000c01v2In2PhFail }
		STATUS current
		DESCRIPTION
			"Audio phase fail Trap"
		::= { hsw3000c01v2Traps 239 }

		-- 1.3.6.1.4.1.10106.2.1.1.364802.3
		hsw3000c01v2In2PreFailTrap NOTIFICATION-TYPE
		OBJECTS { trapCounter, hsw3000c01v2Index, hsw3000c01v2In2PreFail }
		STATUS current
		DESCRIPTION
			"Audio presence fail Trap"
		::= { hsw3000c01v2Traps 241 }

		-- 1.3.6.1.4.1.10106.2.1.1.364802.3
		hsw3000c01v2RefFailTrap NOTIFICATION-TYPE
		OBJECTS { trapCounter, hsw3000c01v2Index, hsw3000c01v2RefFail }
		STATUS current
		DESCRIPTION
			"Reference absence fail Trap"
		::= { hsw3000c01v2Traps 243 }

		-- 1.3.6.1.4.1.10106.2.1.1.364802.3
		hsw3000c01v2LockFailTrap NOTIFICATION-TYPE
		OBJECTS { trapCounter, hsw3000c01v2Index, hsw3000c01v2LockFail }
		STATUS current
		DESCRIPTION
			"Reference unlock fail Trap"
		::= { hsw3000c01v2Traps 245 }

		-- 1.3.6.1.4.1.10106.2.1.1.364802.3
		hsw3000c01v2In1FormatTrap NOTIFICATION-TYPE
		OBJECTS { trapCounter, hsw3000c01v2Index, hsw3000c01v2In1Format }
		STATUS current
		DESCRIPTION
			"Input format Trap"
		::= { hsw3000c01v2Traps 249 }

		-- 1.3.6.1.4.1.10106.2.1.1.364802.3
		hsw3000c01v2In2FormatTrap NOTIFICATION-TYPE
		OBJECTS { trapCounter, hsw3000c01v2Index, hsw3000c01v2In2Format }
		STATUS current
		DESCRIPTION
			"Input format Trap"
		::= { hsw3000c01v2Traps 251 }

		-- 1.3.6.1.4.1.10106.2.1.1.364802.3
		hsw3000c01v2RefFormatTrap NOTIFICATION-TYPE
		OBJECTS { trapCounter, hsw3000c01v2Index, hsw3000c01v2RefFormat }
		STATUS current
		DESCRIPTION
			"Reference format Trap"
		::= { hsw3000c01v2Traps 253 }

		-- 1.3.6.1.4.1.10106.2.1.1.364802.3
		hsw3000c01v2EqualPidTrap NOTIFICATION-TYPE
		OBJECTS { trapCounter, hsw3000c01v2Index, hsw3000c01v2EqualPid }
		STATUS current
		DESCRIPTION
			"Indicates if both  inputs have same PID Trap"
		::= { hsw3000c01v2Traps 263 }

		-- 1.3.6.1.4.1.10106.2.1.1.364802.3
		hsw3000c01v2EqualUmidTrap NOTIFICATION-TYPE
		OBJECTS { trapCounter, hsw3000c01v2Index, hsw3000c01v2EqualUmid }
		STATUS current
		DESCRIPTION
			"Indicates if both  inputs have same UMID Trap"
		::= { hsw3000c01v2Traps 265 }

		-- 1.3.6.1.4.1.10106.2.1.1.364802.3
		hsw3000c01v2In1Grp1PresTrap NOTIFICATION-TYPE
		OBJECTS { trapCounter, hsw3000c01v2Index, hsw3000c01v2In1Grp1Pres }
		STATUS current
		DESCRIPTION
			"Audio group 1 packet presence Trap"
		::= { hsw3000c01v2Traps 275 }

		-- 1.3.6.1.4.1.10106.2.1.1.364802.3
		hsw3000c01v2In1Grp2PresTrap NOTIFICATION-TYPE
		OBJECTS { trapCounter, hsw3000c01v2Index, hsw3000c01v2In1Grp2Pres }
		STATUS current
		DESCRIPTION
			"Audio group 2 packet presence Trap"
		::= { hsw3000c01v2Traps 277 }

		-- 1.3.6.1.4.1.10106.2.1.1.364802.3
		hsw3000c01v2In1Grp3PresTrap NOTIFICATION-TYPE
		OBJECTS { trapCounter, hsw3000c01v2Index, hsw3000c01v2In1Grp3Pres }
		STATUS current
		DESCRIPTION
			"Audio group 3 packet presence Trap"
		::= { hsw3000c01v2Traps 279 }

		-- 1.3.6.1.4.1.10106.2.1.1.364802.3
		hsw3000c01v2In1Grp4PresTrap NOTIFICATION-TYPE
		OBJECTS { trapCounter, hsw3000c01v2Index, hsw3000c01v2In1Grp4Pres }
		STATUS current
		DESCRIPTION
			"Audio group 4 packet presence Trap"
		::= { hsw3000c01v2Traps 281 }

		-- 1.3.6.1.4.1.10106.2.1.1.364802.3
		hsw3000c01v2In1Grp1P0ErrTrap NOTIFICATION-TYPE
		OBJECTS { trapCounter, hsw3000c01v2Index, hsw3000c01v2In1Grp1P0Err }
		STATUS current
		DESCRIPTION
			"Audio group 1 pair 0 fail Trap"
		::= { hsw3000c01v2Traps 283 }

		-- 1.3.6.1.4.1.10106.2.1.1.364802.3
		hsw3000c01v2In1Grp1P1ErrTrap NOTIFICATION-TYPE
		OBJECTS { trapCounter, hsw3000c01v2Index, hsw3000c01v2In1Grp1P1Err }
		STATUS current
		DESCRIPTION
			"Audio group 1 pair 1 fail Trap"
		::= { hsw3000c01v2Traps 285 }

		-- 1.3.6.1.4.1.10106.2.1.1.364802.3
		hsw3000c01v2In1Grp2P0ErrTrap NOTIFICATION-TYPE
		OBJECTS { trapCounter, hsw3000c01v2Index, hsw3000c01v2In1Grp2P0Err }
		STATUS current
		DESCRIPTION
			"Audio group 2 pair 0 fail Trap"
		::= { hsw3000c01v2Traps 287 }

		-- 1.3.6.1.4.1.10106.2.1.1.364802.3
		hsw3000c01v2In1Grp2P1ErrTrap NOTIFICATION-TYPE
		OBJECTS { trapCounter, hsw3000c01v2Index, hsw3000c01v2In1Grp2P1Err }
		STATUS current
		DESCRIPTION
			"Audio group 2 pair 1 fail Trap"
		::= { hsw3000c01v2Traps 289 }

		-- 1.3.6.1.4.1.10106.2.1.1.364802.3
		hsw3000c01v2In1Grp3P0ErrTrap NOTIFICATION-TYPE
		OBJECTS { trapCounter, hsw3000c01v2Index, hsw3000c01v2In1Grp3P0Err }
		STATUS current
		DESCRIPTION
			"Audio group 3 pair 0 fail Trap"
		::= { hsw3000c01v2Traps 291 }

		-- 1.3.6.1.4.1.10106.2.1.1.364802.3
		hsw3000c01v2In1Grp3P1ErrTrap NOTIFICATION-TYPE
		OBJECTS { trapCounter, hsw3000c01v2Index, hsw3000c01v2In1Grp3P1Err }
		STATUS current
		DESCRIPTION
			"Audio group 3 pair 1 fail Trap"
		::= { hsw3000c01v2Traps 293 }

		-- 1.3.6.1.4.1.10106.2.1.1.364802.3
		hsw3000c01v2In1Grp4P0ErrTrap NOTIFICATION-TYPE
		OBJECTS { trapCounter, hsw3000c01v2Index, hsw3000c01v2In1Grp4P0Err }
		STATUS current
		DESCRIPTION
			"Audio group 4 pair 0 fail Trap"
		::= { hsw3000c01v2Traps 295 }

		-- 1.3.6.1.4.1.10106.2.1.1.364802.3
		hsw3000c01v2In1Grp4P1ErrTrap NOTIFICATION-TYPE
		OBJECTS { trapCounter, hsw3000c01v2Index, hsw3000c01v2In1Grp4P1Err }
		STATUS current
		DESCRIPTION
			"Audio group 4 pair 1 fail Trap"
		::= { hsw3000c01v2Traps 297 }

		-- 1.3.6.1.4.1.10106.2.1.1.364802.3
		hsw3000c01v2In2Grp1PresTrap NOTIFICATION-TYPE
		OBJECTS { trapCounter, hsw3000c01v2Index, hsw3000c01v2In2Grp1Pres }
		STATUS current
		DESCRIPTION
			"Audio group 1 packet presence Trap"
		::= { hsw3000c01v2Traps 299 }

		-- 1.3.6.1.4.1.10106.2.1.1.364802.3
		hsw3000c01v2In2Grp2PresTrap NOTIFICATION-TYPE
		OBJECTS { trapCounter, hsw3000c01v2Index, hsw3000c01v2In2Grp2Pres }
		STATUS current
		DESCRIPTION
			"Audio group 2 packet presence Trap"
		::= { hsw3000c01v2Traps 301 }

		-- 1.3.6.1.4.1.10106.2.1.1.364802.3
		hsw3000c01v2In2Grp3PresTrap NOTIFICATION-TYPE
		OBJECTS { trapCounter, hsw3000c01v2Index, hsw3000c01v2In2Grp3Pres }
		STATUS current
		DESCRIPTION
			"Audio group 3 packet presence Trap"
		::= { hsw3000c01v2Traps 303 }

		-- 1.3.6.1.4.1.10106.2.1.1.364802.3
		hsw3000c01v2In2Grp4PresTrap NOTIFICATION-TYPE
		OBJECTS { trapCounter, hsw3000c01v2Index, hsw3000c01v2In2Grp4Pres }
		STATUS current
		DESCRIPTION
			"Audio group 4 packet presence Trap"
		::= { hsw3000c01v2Traps 305 }

		-- 1.3.6.1.4.1.10106.2.1.1.364802.3
		hsw3000c01v2In2Grp1P0ErrTrap NOTIFICATION-TYPE
		OBJECTS { trapCounter, hsw3000c01v2Index, hsw3000c01v2In2Grp1P0Err }
		STATUS current
		DESCRIPTION
			"Audio group 1 pair 0 fail Trap"
		::= { hsw3000c01v2Traps 307 }

		-- 1.3.6.1.4.1.10106.2.1.1.364802.3
		hsw3000c01v2In2Grp1P1ErrTrap NOTIFICATION-TYPE
		OBJECTS { trapCounter, hsw3000c01v2Index, hsw3000c01v2In2Grp1P1Err }
		STATUS current
		DESCRIPTION
			"Audio group 1 pair 1 fail Trap"
		::= { hsw3000c01v2Traps 309 }

		-- 1.3.6.1.4.1.10106.2.1.1.364802.3
		hsw3000c01v2In2Grp2P0ErrTrap NOTIFICATION-TYPE
		OBJECTS { trapCounter, hsw3000c01v2Index, hsw3000c01v2In2Grp2P0Err }
		STATUS current
		DESCRIPTION
			"Audio group 2 pair 0 fail Trap"
		::= { hsw3000c01v2Traps 311 }

		-- 1.3.6.1.4.1.10106.2.1.1.364802.3
		hsw3000c01v2In2Grp2P1ErrTrap NOTIFICATION-TYPE
		OBJECTS { trapCounter, hsw3000c01v2Index, hsw3000c01v2In2Grp2P1Err }
		STATUS current
		DESCRIPTION
			"Audio group 2 pair 1 fail Trap"
		::= { hsw3000c01v2Traps 313 }

		-- 1.3.6.1.4.1.10106.2.1.1.364802.3
		hsw3000c01v2In2Grp3P0ErrTrap NOTIFICATION-TYPE
		OBJECTS { trapCounter, hsw3000c01v2Index, hsw3000c01v2In2Grp3P0Err }
		STATUS current
		DESCRIPTION
			"Audio group 3 pair 0 fail Trap"
		::= { hsw3000c01v2Traps 315 }

		-- 1.3.6.1.4.1.10106.2.1.1.364802.3
		hsw3000c01v2In2Grp3P1ErrTrap NOTIFICATION-TYPE
		OBJECTS { trapCounter, hsw3000c01v2Index, hsw3000c01v2In2Grp3P1Err }
		STATUS current
		DESCRIPTION
			"Audio group 3 pair 1 fail Trap"
		::= { hsw3000c01v2Traps 317 }

		-- 1.3.6.1.4.1.10106.2.1.1.364802.3
		hsw3000c01v2In2Grp4P0ErrTrap NOTIFICATION-TYPE
		OBJECTS { trapCounter, hsw3000c01v2Index, hsw3000c01v2In2Grp4P0Err }
		STATUS current
		DESCRIPTION
			"Audio group 4 pair 0 fail Trap"
		::= { hsw3000c01v2Traps 319 }

		-- 1.3.6.1.4.1.10106.2.1.1.364802.3
		hsw3000c01v2In2Grp4P1ErrTrap NOTIFICATION-TYPE
		OBJECTS { trapCounter, hsw3000c01v2Index, hsw3000c01v2In2Grp4P1Err }
		STATUS current
		DESCRIPTION
			"Audio group 4 pair 1 fail Trap"
		::= { hsw3000c01v2Traps 321 }

		-- 1.3.6.1.4.1.10106.2.1.1.364803
		hsw3000c01v3Traps OBJECT IDENTIFIER ::= { albalaTraps 364803 }

		-- 1.3.6.1.4.1.10106.2.1.1.364803.3
		hsw3000c01v3StateSelTrap NOTIFICATION-TYPE
		OBJECTS { trapCounter, hsw3000c01v3Index, hsw3000c01v3StateSel }
		STATUS current
		DESCRIPTION
			"Shows the module's current state Trap"
		::= { hsw3000c01v3Traps 9 }

		-- 1.3.6.1.4.1.10106.2.1.1.364803.3
		hsw3000c01v3SwitchModeTrap NOTIFICATION-TYPE
		OBJECTS { trapCounter, hsw3000c01v3Index, hsw3000c01v3SwitchMode }
		STATUS current
		DESCRIPTION
			"Allows selecting the switching mode Trap"
		::= { hsw3000c01v3Traps 11 }

		-- 1.3.6.1.4.1.10106.2.1.1.364803.3
		hsw3000c01v3BypassEnableTrap NOTIFICATION-TYPE
		OBJECTS { trapCounter, hsw3000c01v3Index, hsw3000c01v3BypassEnable }
		STATUS current
		DESCRIPTION
			"Allows activating the rear board bypass Trap"
		::= { hsw3000c01v3Traps 15 }

		-- 1.3.6.1.4.1.10106.2.1.1.364803.3
		hsw3000c01v3OperatingModeTrap NOTIFICATION-TYPE
		OBJECTS { trapCounter, hsw3000c01v3Index, hsw3000c01v3OperatingMode }
		STATUS current
		DESCRIPTION
			"Allows selecting the operating mode Trap"
		::= { hsw3000c01v3Traps 19 }

		-- 1.3.6.1.4.1.10106.2.1.1.364803.3
		hsw3000c01v3In1FailTrap NOTIFICATION-TYPE
		OBJECTS { trapCounter, hsw3000c01v3Index, hsw3000c01v3In1Fail }
		STATUS current
		DESCRIPTION
			"Input 1 fail Trap"
		::= { hsw3000c01v3Traps 187 }

		-- 1.3.6.1.4.1.10106.2.1.1.364803.3
		hsw3000c01v3In2FailTrap NOTIFICATION-TYPE
		OBJECTS { trapCounter, hsw3000c01v3Index, hsw3000c01v3In2Fail }
		STATUS current
		DESCRIPTION
			"Input 2 fail Trap"
		::= { hsw3000c01v3Traps 189 }

		-- 1.3.6.1.4.1.10106.2.1.1.364803.3
		hsw3000c01v3In1ExtFailTrap NOTIFICATION-TYPE
		OBJECTS { trapCounter, hsw3000c01v3Index, hsw3000c01v3In1ExtFail }
		STATUS current
		DESCRIPTION
			"Input 1 GPI fail (GPI1A) Trap"
		::= { hsw3000c01v3Traps 191 }

		-- 1.3.6.1.4.1.10106.2.1.1.364803.3
		hsw3000c01v3In2ExtFailTrap NOTIFICATION-TYPE
		OBJECTS { trapCounter, hsw3000c01v3Index, hsw3000c01v3In2ExtFail }
		STATUS current
		DESCRIPTION
			"Input 2 GPI fail (GPI2A) Trap"
		::= { hsw3000c01v3Traps 193 }

		-- 1.3.6.1.4.1.10106.2.1.1.364803.3
		hsw3000c01v3BlindExtFailTrap NOTIFICATION-TYPE
		OBJECTS { trapCounter, hsw3000c01v3Index, hsw3000c01v3BlindExtFail }
		STATUS current
		DESCRIPTION
			"Blind halfauto control GPI fail (GPI2B) Trap"
		::= { hsw3000c01v3Traps 195 }

		-- 1.3.6.1.4.1.10106.2.1.1.364803.3
		hsw3000c01v3EqualPidTrap NOTIFICATION-TYPE
		OBJECTS { trapCounter, hsw3000c01v3Index, hsw3000c01v3EqualPid }
		STATUS current
		DESCRIPTION
			"Indicates if both  inputs have same PID Trap"
		::= { hsw3000c01v3Traps 197 }

		-- 1.3.6.1.4.1.10106.2.1.1.364803.3
		hsw3000c01v3SelOut1Trap NOTIFICATION-TYPE
		OBJECTS { trapCounter, hsw3000c01v3Index, hsw3000c01v3SelOut1 }
		STATUS current
		DESCRIPTION
			"Output 1 Trap"
		::= { hsw3000c01v3Traps 199 }

		-- 1.3.6.1.4.1.10106.2.1.1.364803.3
		hsw3000c01v3SelOut2Trap NOTIFICATION-TYPE
		OBJECTS { trapCounter, hsw3000c01v3Index, hsw3000c01v3SelOut2 }
		STATUS current
		DESCRIPTION
			"Output 2 Trap"
		::= { hsw3000c01v3Traps 201 }

		-- 1.3.6.1.4.1.10106.2.1.1.364803.3
		hsw3000c01v3EqualUmidTrap NOTIFICATION-TYPE
		OBJECTS { trapCounter, hsw3000c01v3Index, hsw3000c01v3EqualUmid }
		STATUS current
		DESCRIPTION
			"Indicates if both  inputs have same UMID Trap"
		::= { hsw3000c01v3Traps 203 }

		-- 1.3.6.1.4.1.10106.2.1.1.364803.3
		hsw3000c01v3Gpi3StatTrap NOTIFICATION-TYPE
		OBJECTS { trapCounter, hsw3000c01v3Index, hsw3000c01v3Gpi3Stat }
		STATUS current
		DESCRIPTION
			"GPI1B status (used in remote control) Trap"
		::= { hsw3000c01v3Traps 205 }

		-- 1.3.6.1.4.1.10106.2.1.1.364803.3
		hsw3000c01v3In1PhyFailTrap NOTIFICATION-TYPE
		OBJECTS { trapCounter, hsw3000c01v3Index, hsw3000c01v3In1PhyFail }
		STATUS current
		DESCRIPTION
			"Absence fail Trap"
		::= { hsw3000c01v3Traps 207 }

		-- 1.3.6.1.4.1.10106.2.1.1.364803.3
		hsw3000c01v3In1FmtFailTrap NOTIFICATION-TYPE
		OBJECTS { trapCounter, hsw3000c01v3Index, hsw3000c01v3In1FmtFail }
		STATUS current
		DESCRIPTION
			"Format fail Trap"
		::= { hsw3000c01v3Traps 209 }

		-- 1.3.6.1.4.1.10106.2.1.1.364803.3
		hsw3000c01v3In1IncFailTrap NOTIFICATION-TYPE
		OBJECTS { trapCounter, hsw3000c01v3Index, hsw3000c01v3In1IncFail }
		STATUS current
		DESCRIPTION
			"Incompatible format fail Trap"
		::= { hsw3000c01v3Traps 211 }

		-- 1.3.6.1.4.1.10106.2.1.1.364803.3
		hsw3000c01v3In1GpiFailTrap NOTIFICATION-TYPE
		OBJECTS { trapCounter, hsw3000c01v3Index, hsw3000c01v3In1GpiFail }
		STATUS current
		DESCRIPTION
			"External GPI fail Trap"
		::= { hsw3000c01v3Traps 213 }

		-- 1.3.6.1.4.1.10106.2.1.1.364803.3
		hsw3000c01v3In1BlkFailTrap NOTIFICATION-TYPE
		OBJECTS { trapCounter, hsw3000c01v3Index, hsw3000c01v3In1BlkFail }
		STATUS current
		DESCRIPTION
			"Black signal fail Trap"
		::= { hsw3000c01v3Traps 215 }

		-- 1.3.6.1.4.1.10106.2.1.1.364803.3
		hsw3000c01v3In1FrzFailTrap NOTIFICATION-TYPE
		OBJECTS { trapCounter, hsw3000c01v3Index, hsw3000c01v3In1FrzFail }
		STATUS current
		DESCRIPTION
			"Freeze signal fail Trap"
		::= { hsw3000c01v3Traps 217 }

		-- 1.3.6.1.4.1.10106.2.1.1.364803.3
		hsw3000c01v3In1PatFailTrap NOTIFICATION-TYPE
		OBJECTS { trapCounter, hsw3000c01v3Index, hsw3000c01v3In1PatFail }
		STATUS current
		DESCRIPTION
			"Video pattern fail Trap"
		::= { hsw3000c01v3Traps 219 }

		-- 1.3.6.1.4.1.10106.2.1.1.364803.3
		hsw3000c01v3In1CrcFailTrap NOTIFICATION-TYPE
		OBJECTS { trapCounter, hsw3000c01v3Index, hsw3000c01v3In1CrcFail }
		STATUS current
		DESCRIPTION
			"EDH/CRC fail Trap"
		::= { hsw3000c01v3Traps 221 }

		-- 1.3.6.1.4.1.10106.2.1.1.364803.3
		hsw3000c01v3In1SilFailTrap NOTIFICATION-TYPE
		OBJECTS { trapCounter, hsw3000c01v3Index, hsw3000c01v3In1SilFail }
		STATUS current
		DESCRIPTION
			"Audio silence fail Trap"
		::= { hsw3000c01v3Traps 223 }

		-- 1.3.6.1.4.1.10106.2.1.1.364803.3
		hsw3000c01v3In1OvrFailTrap NOTIFICATION-TYPE
		OBJECTS { trapCounter, hsw3000c01v3Index, hsw3000c01v3In1OvrFail }
		STATUS current
		DESCRIPTION
			"Audio overload fail Trap"
		::= { hsw3000c01v3Traps 225 }

		-- 1.3.6.1.4.1.10106.2.1.1.364803.3
		hsw3000c01v3In1PhFailTrap NOTIFICATION-TYPE
		OBJECTS { trapCounter, hsw3000c01v3Index, hsw3000c01v3In1PhFail }
		STATUS current
		DESCRIPTION
			"Audio phase fail Trap"
		::= { hsw3000c01v3Traps 227 }

		-- 1.3.6.1.4.1.10106.2.1.1.364803.3
		hsw3000c01v3In1PreFailTrap NOTIFICATION-TYPE
		OBJECTS { trapCounter, hsw3000c01v3Index, hsw3000c01v3In1PreFail }
		STATUS current
		DESCRIPTION
			"Audio presence fail Trap"
		::= { hsw3000c01v3Traps 229 }

		-- 1.3.6.1.4.1.10106.2.1.1.364803.3
		hsw3000c01v3In2PhyFailTrap NOTIFICATION-TYPE
		OBJECTS { trapCounter, hsw3000c01v3Index, hsw3000c01v3In2PhyFail }
		STATUS current
		DESCRIPTION
			"Absence fail Trap"
		::= { hsw3000c01v3Traps 231 }

		-- 1.3.6.1.4.1.10106.2.1.1.364803.3
		hsw3000c01v3In2FmtFailTrap NOTIFICATION-TYPE
		OBJECTS { trapCounter, hsw3000c01v3Index, hsw3000c01v3In2FmtFail }
		STATUS current
		DESCRIPTION
			"Format fail Trap"
		::= { hsw3000c01v3Traps 233 }

		-- 1.3.6.1.4.1.10106.2.1.1.364803.3
		hsw3000c01v3In2IncFailTrap NOTIFICATION-TYPE
		OBJECTS { trapCounter, hsw3000c01v3Index, hsw3000c01v3In2IncFail }
		STATUS current
		DESCRIPTION
			"Incompatible format fail Trap"
		::= { hsw3000c01v3Traps 235 }

		-- 1.3.6.1.4.1.10106.2.1.1.364803.3
		hsw3000c01v3In2GpiFailTrap NOTIFICATION-TYPE
		OBJECTS { trapCounter, hsw3000c01v3Index, hsw3000c01v3In2GpiFail }
		STATUS current
		DESCRIPTION
			"External GPI fail Trap"
		::= { hsw3000c01v3Traps 237 }

		-- 1.3.6.1.4.1.10106.2.1.1.364803.3
		hsw3000c01v3In2BlkFailTrap NOTIFICATION-TYPE
		OBJECTS { trapCounter, hsw3000c01v3Index, hsw3000c01v3In2BlkFail }
		STATUS current
		DESCRIPTION
			"Black signal fail Trap"
		::= { hsw3000c01v3Traps 239 }

		-- 1.3.6.1.4.1.10106.2.1.1.364803.3
		hsw3000c01v3In2FrzFailTrap NOTIFICATION-TYPE
		OBJECTS { trapCounter, hsw3000c01v3Index, hsw3000c01v3In2FrzFail }
		STATUS current
		DESCRIPTION
			"Freeze signal fail Trap"
		::= { hsw3000c01v3Traps 241 }

		-- 1.3.6.1.4.1.10106.2.1.1.364803.3
		hsw3000c01v3In2PatFailTrap NOTIFICATION-TYPE
		OBJECTS { trapCounter, hsw3000c01v3Index, hsw3000c01v3In2PatFail }
		STATUS current
		DESCRIPTION
			"Video pattern fail Trap"
		::= { hsw3000c01v3Traps 243 }

		-- 1.3.6.1.4.1.10106.2.1.1.364803.3
		hsw3000c01v3In2CrcFailTrap NOTIFICATION-TYPE
		OBJECTS { trapCounter, hsw3000c01v3Index, hsw3000c01v3In2CrcFail }
		STATUS current
		DESCRIPTION
			"EDH/CRC fail Trap"
		::= { hsw3000c01v3Traps 245 }

		-- 1.3.6.1.4.1.10106.2.1.1.364803.3
		hsw3000c01v3In2SilFailTrap NOTIFICATION-TYPE
		OBJECTS { trapCounter, hsw3000c01v3Index, hsw3000c01v3In2SilFail }
		STATUS current
		DESCRIPTION
			"Audio silence fail Trap"
		::= { hsw3000c01v3Traps 247 }

		-- 1.3.6.1.4.1.10106.2.1.1.364803.3
		hsw3000c01v3In2OvrFailTrap NOTIFICATION-TYPE
		OBJECTS { trapCounter, hsw3000c01v3Index, hsw3000c01v3In2OvrFail }
		STATUS current
		DESCRIPTION
			"Audio overload fail Trap"
		::= { hsw3000c01v3Traps 249 }

		-- 1.3.6.1.4.1.10106.2.1.1.364803.3
		hsw3000c01v3In2PhFailTrap NOTIFICATION-TYPE
		OBJECTS { trapCounter, hsw3000c01v3Index, hsw3000c01v3In2PhFail }
		STATUS current
		DESCRIPTION
			"Audio phase fail Trap"
		::= { hsw3000c01v3Traps 251 }

		-- 1.3.6.1.4.1.10106.2.1.1.364803.3
		hsw3000c01v3In2PreFailTrap NOTIFICATION-TYPE
		OBJECTS { trapCounter, hsw3000c01v3Index, hsw3000c01v3In2PreFail }
		STATUS current
		DESCRIPTION
			"Audio presence fail Trap"
		::= { hsw3000c01v3Traps 253 }

		-- 1.3.6.1.4.1.10106.2.1.1.364803.3
		hsw3000c01v3RefFailTrap NOTIFICATION-TYPE
		OBJECTS { trapCounter, hsw3000c01v3Index, hsw3000c01v3RefFail }
		STATUS current
		DESCRIPTION
			"Reference absence fail Trap"
		::= { hsw3000c01v3Traps 255 }

		-- 1.3.6.1.4.1.10106.2.1.1.364803.3
		hsw3000c01v3LockFailTrap NOTIFICATION-TYPE
		OBJECTS { trapCounter, hsw3000c01v3Index, hsw3000c01v3LockFail }
		STATUS current
		DESCRIPTION
			"Reference unlock fail Trap"
		::= { hsw3000c01v3Traps 257 }

		-- 1.3.6.1.4.1.10106.2.1.1.364803.3
		hsw3000c01v3In1FormatTrap NOTIFICATION-TYPE
		OBJECTS { trapCounter, hsw3000c01v3Index, hsw3000c01v3In1Format }
		STATUS current
		DESCRIPTION
			"Input format Trap"
		::= { hsw3000c01v3Traps 261 }

		-- 1.3.6.1.4.1.10106.2.1.1.364803.3
		hsw3000c01v3In2FormatTrap NOTIFICATION-TYPE
		OBJECTS { trapCounter, hsw3000c01v3Index, hsw3000c01v3In2Format }
		STATUS current
		DESCRIPTION
			"Input format Trap"
		::= { hsw3000c01v3Traps 263 }

		-- 1.3.6.1.4.1.10106.2.1.1.364803.3
		hsw3000c01v3RefFormatTrap NOTIFICATION-TYPE
		OBJECTS { trapCounter, hsw3000c01v3Index, hsw3000c01v3RefFormat }
		STATUS current
		DESCRIPTION
			"Reference format Trap"
		::= { hsw3000c01v3Traps 265 }

		-- 1.3.6.1.4.1.10106.2.1.1.364803.3
		hsw3000c01v3In1Grp1PresTrap NOTIFICATION-TYPE
		OBJECTS { trapCounter, hsw3000c01v3Index, hsw3000c01v3In1Grp1Pres }
		STATUS current
		DESCRIPTION
			"Audio group 1 packet presence Trap"
		::= { hsw3000c01v3Traps 275 }

		-- 1.3.6.1.4.1.10106.2.1.1.364803.3
		hsw3000c01v3In1Grp2PresTrap NOTIFICATION-TYPE
		OBJECTS { trapCounter, hsw3000c01v3Index, hsw3000c01v3In1Grp2Pres }
		STATUS current
		DESCRIPTION
			"Audio group 2 packet presence Trap"
		::= { hsw3000c01v3Traps 277 }

		-- 1.3.6.1.4.1.10106.2.1.1.364803.3
		hsw3000c01v3In1Grp3PresTrap NOTIFICATION-TYPE
		OBJECTS { trapCounter, hsw3000c01v3Index, hsw3000c01v3In1Grp3Pres }
		STATUS current
		DESCRIPTION
			"Audio group 3 packet presence Trap"
		::= { hsw3000c01v3Traps 279 }

		-- 1.3.6.1.4.1.10106.2.1.1.364803.3
		hsw3000c01v3In1Grp4PresTrap NOTIFICATION-TYPE
		OBJECTS { trapCounter, hsw3000c01v3Index, hsw3000c01v3In1Grp4Pres }
		STATUS current
		DESCRIPTION
			"Audio group 4 packet presence Trap"
		::= { hsw3000c01v3Traps 281 }

		-- 1.3.6.1.4.1.10106.2.1.1.364803.3
		hsw3000c01v3In1Grp1P0StatTrap NOTIFICATION-TYPE
		OBJECTS { trapCounter, hsw3000c01v3Index, hsw3000c01v3In1Grp1P0Stat }
		STATUS current
		DESCRIPTION
			"Audio group 1 pair 0 status Trap"
		::= { hsw3000c01v3Traps 283 }

		-- 1.3.6.1.4.1.10106.2.1.1.364803.3
		hsw3000c01v3In1Grp1P1StatTrap NOTIFICATION-TYPE
		OBJECTS { trapCounter, hsw3000c01v3Index, hsw3000c01v3In1Grp1P1Stat }
		STATUS current
		DESCRIPTION
			"Audio group 1 pair 1 status Trap"
		::= { hsw3000c01v3Traps 285 }

		-- 1.3.6.1.4.1.10106.2.1.1.364803.3
		hsw3000c01v3In1Grp2P0StatTrap NOTIFICATION-TYPE
		OBJECTS { trapCounter, hsw3000c01v3Index, hsw3000c01v3In1Grp2P0Stat }
		STATUS current
		DESCRIPTION
			"Audio group 2 pair 0 status Trap"
		::= { hsw3000c01v3Traps 287 }

		-- 1.3.6.1.4.1.10106.2.1.1.364803.3
		hsw3000c01v3In1Grp2P1StatTrap NOTIFICATION-TYPE
		OBJECTS { trapCounter, hsw3000c01v3Index, hsw3000c01v3In1Grp2P1Stat }
		STATUS current
		DESCRIPTION
			"Audio group 2 pair 1 status Trap"
		::= { hsw3000c01v3Traps 289 }

		-- 1.3.6.1.4.1.10106.2.1.1.364803.3
		hsw3000c01v3In1Grp3P0StatTrap NOTIFICATION-TYPE
		OBJECTS { trapCounter, hsw3000c01v3Index, hsw3000c01v3In1Grp3P0Stat }
		STATUS current
		DESCRIPTION
			"Audio group 3 pair 0 status Trap"
		::= { hsw3000c01v3Traps 291 }

		-- 1.3.6.1.4.1.10106.2.1.1.364803.3
		hsw3000c01v3In1Grp3P1StatTrap NOTIFICATION-TYPE
		OBJECTS { trapCounter, hsw3000c01v3Index, hsw3000c01v3In1Grp3P1Stat }
		STATUS current
		DESCRIPTION
			"Audio group 3 pair 1 status Trap"
		::= { hsw3000c01v3Traps 293 }

		-- 1.3.6.1.4.1.10106.2.1.1.364803.3
		hsw3000c01v3In1Grp4P0StatTrap NOTIFICATION-TYPE
		OBJECTS { trapCounter, hsw3000c01v3Index, hsw3000c01v3In1Grp4P0Stat }
		STATUS current
		DESCRIPTION
			"Audio group 4 pair 0 status Trap"
		::= { hsw3000c01v3Traps 295 }

		-- 1.3.6.1.4.1.10106.2.1.1.364803.3
		hsw3000c01v3In1Grp4P1StatTrap NOTIFICATION-TYPE
		OBJECTS { trapCounter, hsw3000c01v3Index, hsw3000c01v3In1Grp4P1Stat }
		STATUS current
		DESCRIPTION
			"Audio group 4 pair 1 status Trap"
		::= { hsw3000c01v3Traps 297 }

		-- 1.3.6.1.4.1.10106.2.1.1.364803.3
		hsw3000c01v3In2Grp1PresTrap NOTIFICATION-TYPE
		OBJECTS { trapCounter, hsw3000c01v3Index, hsw3000c01v3In2Grp1Pres }
		STATUS current
		DESCRIPTION
			"Audio group 1 packet presence Trap"
		::= { hsw3000c01v3Traps 299 }

		-- 1.3.6.1.4.1.10106.2.1.1.364803.3
		hsw3000c01v3In2Grp2PresTrap NOTIFICATION-TYPE
		OBJECTS { trapCounter, hsw3000c01v3Index, hsw3000c01v3In2Grp2Pres }
		STATUS current
		DESCRIPTION
			"Audio group 2 packet presence Trap"
		::= { hsw3000c01v3Traps 301 }

		-- 1.3.6.1.4.1.10106.2.1.1.364803.3
		hsw3000c01v3In2Grp3PresTrap NOTIFICATION-TYPE
		OBJECTS { trapCounter, hsw3000c01v3Index, hsw3000c01v3In2Grp3Pres }
		STATUS current
		DESCRIPTION
			"Audio group 3 packet presence Trap"
		::= { hsw3000c01v3Traps 303 }

		-- 1.3.6.1.4.1.10106.2.1.1.364803.3
		hsw3000c01v3In2Grp4PresTrap NOTIFICATION-TYPE
		OBJECTS { trapCounter, hsw3000c01v3Index, hsw3000c01v3In2Grp4Pres }
		STATUS current
		DESCRIPTION
			"Audio group 4 packet presence Trap"
		::= { hsw3000c01v3Traps 305 }

		-- 1.3.6.1.4.1.10106.2.1.1.364803.3
		hsw3000c01v3In2Grp1P0StatTrap NOTIFICATION-TYPE
		OBJECTS { trapCounter, hsw3000c01v3Index, hsw3000c01v3In2Grp1P0Stat }
		STATUS current
		DESCRIPTION
			"Audio group 1 pair 0 status Trap"
		::= { hsw3000c01v3Traps 307 }

		-- 1.3.6.1.4.1.10106.2.1.1.364803.3
		hsw3000c01v3In2Grp1P1StatTrap NOTIFICATION-TYPE
		OBJECTS { trapCounter, hsw3000c01v3Index, hsw3000c01v3In2Grp1P1Stat }
		STATUS current
		DESCRIPTION
			"Audio group 1 pair 1 status Trap"
		::= { hsw3000c01v3Traps 309 }

		-- 1.3.6.1.4.1.10106.2.1.1.364803.3
		hsw3000c01v3In2Grp2P0StatTrap NOTIFICATION-TYPE
		OBJECTS { trapCounter, hsw3000c01v3Index, hsw3000c01v3In2Grp2P0Stat }
		STATUS current
		DESCRIPTION
			"Audio group 2 pair 0 status Trap"
		::= { hsw3000c01v3Traps 311 }

		-- 1.3.6.1.4.1.10106.2.1.1.364803.3
		hsw3000c01v3In2Grp2P1StatTrap NOTIFICATION-TYPE
		OBJECTS { trapCounter, hsw3000c01v3Index, hsw3000c01v3In2Grp2P1Stat }
		STATUS current
		DESCRIPTION
			"Audio group 2 pair 1status Trap"
		::= { hsw3000c01v3Traps 313 }

		-- 1.3.6.1.4.1.10106.2.1.1.364803.3
		hsw3000c01v3In2Grp3P0StatTrap NOTIFICATION-TYPE
		OBJECTS { trapCounter, hsw3000c01v3Index, hsw3000c01v3In2Grp3P0Stat }
		STATUS current
		DESCRIPTION
			"Audio group 3 pair 0 status Trap"
		::= { hsw3000c01v3Traps 315 }

		-- 1.3.6.1.4.1.10106.2.1.1.364803.3
		hsw3000c01v3In2Grp3P1StatTrap NOTIFICATION-TYPE
		OBJECTS { trapCounter, hsw3000c01v3Index, hsw3000c01v3In2Grp3P1Stat }
		STATUS current
		DESCRIPTION
			"Audio group 3 pair 1 status Trap"
		::= { hsw3000c01v3Traps 317 }

		-- 1.3.6.1.4.1.10106.2.1.1.364803.3
		hsw3000c01v3In2Grp4P0StatTrap NOTIFICATION-TYPE
		OBJECTS { trapCounter, hsw3000c01v3Index, hsw3000c01v3In2Grp4P0Stat }
		STATUS current
		DESCRIPTION
			"Audio group 4 pair 0 status Trap"
		::= { hsw3000c01v3Traps 319 }

		-- 1.3.6.1.4.1.10106.2.1.1.364803.3
		hsw3000c01v3In2Grp4P1StatTrap NOTIFICATION-TYPE
		OBJECTS { trapCounter, hsw3000c01v3Index, hsw3000c01v3In2Grp4P1Stat }
		STATUS current
		DESCRIPTION
			"Audio group 4 pair 1 status Trap"
		::= { hsw3000c01v3Traps 321 }

		-- 1.3.6.1.4.1.10106.2.1.1.364803.3
		hsw3000c01v3In1WssStatTrap NOTIFICATION-TYPE
		OBJECTS { trapCounter, hsw3000c01v3Index, hsw3000c01v3In1WssStat }
		STATUS current
		DESCRIPTION
			"WSS information Trap"
		::= { hsw3000c01v3Traps 323 }

		-- 1.3.6.1.4.1.10106.2.1.1.364803.3
		hsw3000c01v3In1ViiStatTrap NOTIFICATION-TYPE
		OBJECTS { trapCounter, hsw3000c01v3Index, hsw3000c01v3In1ViiStat }
		STATUS current
		DESCRIPTION
			"VII information Trap"
		::= { hsw3000c01v3Traps 325 }

		-- 1.3.6.1.4.1.10106.2.1.1.364803.3
		hsw3000c01v3In12016StatTrap NOTIFICATION-TYPE
		OBJECTS { trapCounter, hsw3000c01v3Index, hsw3000c01v3In12016Stat }
		STATUS current
		DESCRIPTION
			"SMPTE 2016 information Trap"
		::= { hsw3000c01v3Traps 327 }

		-- 1.3.6.1.4.1.10106.2.1.1.364803.3
		hsw3000c01v3In2WssStatTrap NOTIFICATION-TYPE
		OBJECTS { trapCounter, hsw3000c01v3Index, hsw3000c01v3In2WssStat }
		STATUS current
		DESCRIPTION
			"WSS information Trap"
		::= { hsw3000c01v3Traps 329 }

		-- 1.3.6.1.4.1.10106.2.1.1.364803.3
		hsw3000c01v3In2ViiStatTrap NOTIFICATION-TYPE
		OBJECTS { trapCounter, hsw3000c01v3Index, hsw3000c01v3In2ViiStat }
		STATUS current
		DESCRIPTION
			"VII information Trap"
		::= { hsw3000c01v3Traps 331 }

		-- 1.3.6.1.4.1.10106.2.1.1.364803.3
		hsw3000c01v3In22016StatTrap NOTIFICATION-TYPE
		OBJECTS { trapCounter, hsw3000c01v3Index, hsw3000c01v3In22016Stat }
		STATUS current
		DESCRIPTION
			"SMPTE 2016 information Trap"
		::= { hsw3000c01v3Traps 333 }

		-- 1.3.6.1.4.1.10106.2.1.1.364803.3
		hsw3000c01v3In1TxtLinLowTrap NOTIFICATION-TYPE
		OBJECTS { trapCounter, hsw3000c01v3Index, hsw3000c01v3In1TxtLinLow }
		STATUS current
		DESCRIPTION
			"Low level of teletext lines Trap"
		::= { hsw3000c01v3Traps 335 }

		-- 1.3.6.1.4.1.10106.2.1.1.364803.3
		hsw3000c01v3In2TxtLinLowTrap NOTIFICATION-TYPE
		OBJECTS { trapCounter, hsw3000c01v3Index, hsw3000c01v3In2TxtLinLow }
		STATUS current
		DESCRIPTION
			"Low level of teletext lines Trap"
		::= { hsw3000c01v3Traps 339 }

		-- 1.3.6.1.4.1.10106.2.1.1.364803.3
		hsw3000c01v3In1WssCodTrap NOTIFICATION-TYPE
		OBJECTS { trapCounter, hsw3000c01v3Index, hsw3000c01v3In1WssCod }
		STATUS current
		DESCRIPTION
			"WSS group 1 data  (b3-b0) Trap"
		::= { hsw3000c01v3Traps 353 }

		-- 1.3.6.1.4.1.10106.2.1.1.364803.3
		hsw3000c01v3In1ViiAfdCodTrap NOTIFICATION-TYPE
		OBJECTS { trapCounter, hsw3000c01v3Index, hsw3000c01v3In1ViiAfdCod }
		STATUS current
		DESCRIPTION
			"VII AFD code (a3-a0) Trap"
		::= { hsw3000c01v3Traps 355 }

		-- 1.3.6.1.4.1.10106.2.1.1.364803.3
		hsw3000c01v3In12016AfdCodTrap NOTIFICATION-TYPE
		OBJECTS { trapCounter, hsw3000c01v3Index, hsw3000c01v3In12016AfdCod }
		STATUS current
		DESCRIPTION
			"SMPTE 2016 AFD code (a3-a0) Trap"
		::= { hsw3000c01v3Traps 357 }

		-- 1.3.6.1.4.1.10106.2.1.1.364803.3
		hsw3000c01v3In2WssCodTrap NOTIFICATION-TYPE
		OBJECTS { trapCounter, hsw3000c01v3Index, hsw3000c01v3In2WssCod }
		STATUS current
		DESCRIPTION
			"WSS group 1 data  (b3-b0) Trap"
		::= { hsw3000c01v3Traps 359 }

		-- 1.3.6.1.4.1.10106.2.1.1.364803.3
		hsw3000c01v3In2ViiAfdCodTrap NOTIFICATION-TYPE
		OBJECTS { trapCounter, hsw3000c01v3Index, hsw3000c01v3In2ViiAfdCod }
		STATUS current
		DESCRIPTION
			"VII AFD code (a3-a0) Trap"
		::= { hsw3000c01v3Traps 361 }

		-- 1.3.6.1.4.1.10106.2.1.1.364803.3
		hsw3000c01v3In22016CodTrap NOTIFICATION-TYPE
		OBJECTS { trapCounter, hsw3000c01v3Index, hsw3000c01v3In22016Cod }
		STATUS current
		DESCRIPTION
			"SMPTE 2016 AFD code (a3-a0) Trap"
		::= { hsw3000c01v3Traps 363 }

		-- 1.3.6.1.4.1.10106.2.1.1.371701
		eop0020c01v1Traps OBJECT IDENTIFIER ::= { albalaTraps 371701 }

		-- 1.3.6.1.4.1.10106.2.1.1.371701.3
		eop0020c01v1NoSigATrap NOTIFICATION-TYPE
		OBJECTS { trapCounter, eop0020c01v1Index, eop0020c01v1NoSigA }
		STATUS current
		DESCRIPTION
			"Input signal status Trap"
		::= { eop0020c01v1Traps 5 }

		-- 1.3.6.1.4.1.10106.2.1.1.371701.3
		eop0020c01v1UnlockATrap NOTIFICATION-TYPE
		OBJECTS { trapCounter, eop0020c01v1Index, eop0020c01v1UnlockA }
		STATUS current
		DESCRIPTION
			"Indicates signal unlock fail Trap"
		::= { eop0020c01v1Traps 7 }

		-- 1.3.6.1.4.1.10106.2.1.1.371701.3
		eop0020c01v1LFailATrap NOTIFICATION-TYPE
		OBJECTS { trapCounter, eop0020c01v1Index, eop0020c01v1LFailA }
		STATUS current
		DESCRIPTION
			"Indicates a fail in laser Trap"
		::= { eop0020c01v1Traps 9 }

		-- 1.3.6.1.4.1.10106.2.1.1.371701.3
		eop0020c01v1NoSigBTrap NOTIFICATION-TYPE
		OBJECTS { trapCounter, eop0020c01v1Index, eop0020c01v1NoSigB }
		STATUS current
		DESCRIPTION
			"Input signal status Trap"
		::= { eop0020c01v1Traps 11 }

		-- 1.3.6.1.4.1.10106.2.1.1.371701.3
		eop0020c01v1UnlockBTrap NOTIFICATION-TYPE
		OBJECTS { trapCounter, eop0020c01v1Index, eop0020c01v1UnlockB }
		STATUS current
		DESCRIPTION
			"Indicates signal unlock fail Trap"
		::= { eop0020c01v1Traps 13 }

		-- 1.3.6.1.4.1.10106.2.1.1.371701.3
		eop0020c01v1LFailBTrap NOTIFICATION-TYPE
		OBJECTS { trapCounter, eop0020c01v1Index, eop0020c01v1LFailB }
		STATUS current
		DESCRIPTION
			"Indicates a fail in laser Trap"
		::= { eop0020c01v1Traps 15 }

		-- 1.3.6.1.4.1.10106.2.1.1.373501
		hop3147c01v1Traps OBJECT IDENTIFIER ::= { albalaTraps 373501 }

		-- 1.3.6.1.4.1.10106.2.1.1.373501.3
		hop3147c01v1NoSignalTrap NOTIFICATION-TYPE
		OBJECTS { trapCounter, hop3147c01v1Index, hop3147c01v1NoSignal }
		STATUS current
		DESCRIPTION
			"There is no SDI signal or the format is not supported Trap"
		::= { hop3147c01v1Traps 29 }

		-- 1.3.6.1.4.1.10106.2.1.1.373501.3
		hop3147c01v1UnlockTrap NOTIFICATION-TYPE
		OBJECTS { trapCounter, hop3147c01v1Index, hop3147c01v1Unlock }
		STATUS current
		DESCRIPTION
			"Indicates signal unlock fail Trap"
		::= { hop3147c01v1Traps 31 }

		-- 1.3.6.1.4.1.10106.2.1.1.373501.3
		hop3147c01v1EdhErrorTrap NOTIFICATION-TYPE
		OBJECTS { trapCounter, hop3147c01v1Index, hop3147c01v1EdhError }
		STATUS current
		DESCRIPTION
			"There are EDH/CRC errors on SDI signal Trap"
		::= { hop3147c01v1Traps 33 }

		-- 1.3.6.1.4.1.10106.2.1.1.373501.3
		hop3147c01v1TxtFailTrap NOTIFICATION-TYPE
		OBJECTS { trapCounter, hop3147c01v1Index, hop3147c01v1TxtFail }
		STATUS current
		DESCRIPTION
			"Teletext signal not found Trap"
		::= { hop3147c01v1Traps 35 }

		-- 1.3.6.1.4.1.10106.2.1.1.373501.3
		hop3147c01v1TxtInsFailTrap NOTIFICATION-TYPE
		OBJECTS { trapCounter, hop3147c01v1Index, hop3147c01v1TxtInsFail }
		STATUS current
		DESCRIPTION
			"OP47 packet can not be insertedl Trap"
		::= { hop3147c01v1Traps 37 }

		-- 1.3.6.1.4.1.10106.2.1.1.373501.3
		hop3147c01v1Gpi1Trap NOTIFICATION-TYPE
		OBJECTS { trapCounter, hop3147c01v1Index, hop3147c01v1Gpi1 }
		STATUS current
		DESCRIPTION
			"Transmitted GPI1 Trap"
		::= { hop3147c01v1Traps 41 }

		-- 1.3.6.1.4.1.10106.2.1.1.373501.3
		hop3147c01v1Gpi2Trap NOTIFICATION-TYPE
		OBJECTS { trapCounter, hop3147c01v1Index, hop3147c01v1Gpi2 }
		STATUS current
		DESCRIPTION
			"Transmitted GPI2 Trap"
		::= { hop3147c01v1Traps 43 }

		-- 1.3.6.1.4.1.10106.2.1.1.373501.3
		hop3147c01v1Gpi3Trap NOTIFICATION-TYPE
		OBJECTS { trapCounter, hop3147c01v1Index, hop3147c01v1Gpi3 }
		STATUS current
		DESCRIPTION
			"Transmitted GPI3 Trap"
		::= { hop3147c01v1Traps 45 }

		-- 1.3.6.1.4.1.10106.2.1.1.373501.3
		hop3147c01v1Gpi4Trap NOTIFICATION-TYPE
		OBJECTS { trapCounter, hop3147c01v1Index, hop3147c01v1Gpi4 }
		STATUS current
		DESCRIPTION
			"Transmitted GPI4 Trap"
		::= { hop3147c01v1Traps 47 }

		-- 1.3.6.1.4.1.10106.2.1.1.373501.3
		hop3147c01v1Gpi5Trap NOTIFICATION-TYPE
		OBJECTS { trapCounter, hop3147c01v1Index, hop3147c01v1Gpi5 }
		STATUS current
		DESCRIPTION
			"Transmitted GPI5 Trap"
		::= { hop3147c01v1Traps 49 }

		-- 1.3.6.1.4.1.10106.2.1.1.373501.3
		hop3147c01v1Gpi6Trap NOTIFICATION-TYPE
		OBJECTS { trapCounter, hop3147c01v1Index, hop3147c01v1Gpi6 }
		STATUS current
		DESCRIPTION
			"Transmitted GPI6 Trap"
		::= { hop3147c01v1Traps 51 }

		-- 1.3.6.1.4.1.10106.2.1.1.373501.3
		hop3147c01v1Gpi7Trap NOTIFICATION-TYPE
		OBJECTS { trapCounter, hop3147c01v1Index, hop3147c01v1Gpi7 }
		STATUS current
		DESCRIPTION
			"Transmitted GPI7 Trap"
		::= { hop3147c01v1Traps 53 }

		-- 1.3.6.1.4.1.10106.2.1.1.373501.3
		hop3147c01v1Gpi8Trap NOTIFICATION-TYPE
		OBJECTS { trapCounter, hop3147c01v1Index, hop3147c01v1Gpi8 }
		STATUS current
		DESCRIPTION
			"Transmitted GPI8 Trap"
		::= { hop3147c01v1Traps 55 }

		-- 1.3.6.1.4.1.10106.2.1.1.373501.3
		hop3147c01v1Gpo1Trap NOTIFICATION-TYPE
		OBJECTS { trapCounter, hop3147c01v1Index, hop3147c01v1Gpo1 }
		STATUS current
		DESCRIPTION
			"Received GPO1 Trap"
		::= { hop3147c01v1Traps 57 }

		-- 1.3.6.1.4.1.10106.2.1.1.373501.3
		hop3147c01v1Gpo2Trap NOTIFICATION-TYPE
		OBJECTS { trapCounter, hop3147c01v1Index, hop3147c01v1Gpo2 }
		STATUS current
		DESCRIPTION
			"Received GPO2 Trap"
		::= { hop3147c01v1Traps 59 }

		-- 1.3.6.1.4.1.10106.2.1.1.373501.3
		hop3147c01v1Gpo3Trap NOTIFICATION-TYPE
		OBJECTS { trapCounter, hop3147c01v1Index, hop3147c01v1Gpo3 }
		STATUS current
		DESCRIPTION
			"Received GPO3 Trap"
		::= { hop3147c01v1Traps 61 }

		-- 1.3.6.1.4.1.10106.2.1.1.373501.3
		hop3147c01v1Gpo4Trap NOTIFICATION-TYPE
		OBJECTS { trapCounter, hop3147c01v1Index, hop3147c01v1Gpo4 }
		STATUS current
		DESCRIPTION
			"Received GPO4 Trap"
		::= { hop3147c01v1Traps 63 }

		-- 1.3.6.1.4.1.10106.2.1.1.373501.3
		hop3147c01v1Gpo5Trap NOTIFICATION-TYPE
		OBJECTS { trapCounter, hop3147c01v1Index, hop3147c01v1Gpo5 }
		STATUS current
		DESCRIPTION
			"Received GPO5 Trap"
		::= { hop3147c01v1Traps 65 }

		-- 1.3.6.1.4.1.10106.2.1.1.373501.3
		hop3147c01v1Gpo6Trap NOTIFICATION-TYPE
		OBJECTS { trapCounter, hop3147c01v1Index, hop3147c01v1Gpo6 }
		STATUS current
		DESCRIPTION
			"Received GPO6 Trap"
		::= { hop3147c01v1Traps 67 }

		-- 1.3.6.1.4.1.10106.2.1.1.373501.3
		hop3147c01v1Gpo7Trap NOTIFICATION-TYPE
		OBJECTS { trapCounter, hop3147c01v1Index, hop3147c01v1Gpo7 }
		STATUS current
		DESCRIPTION
			"Received GPO7 Trap"
		::= { hop3147c01v1Traps 69 }

		-- 1.3.6.1.4.1.10106.2.1.1.373501.3
		hop3147c01v1Gpo8Trap NOTIFICATION-TYPE
		OBJECTS { trapCounter, hop3147c01v1Index, hop3147c01v1Gpo8 }
		STATUS current
		DESCRIPTION
			"Received GPO8 Trap"
		::= { hop3147c01v1Traps 71 }

		-- 1.3.6.1.4.1.10106.2.1.1.375001
		hvp3000c01v1Traps OBJECT IDENTIFIER ::= { albalaTraps 375001 }

		-- 1.3.6.1.4.1.10106.2.1.1.375001.3
		hvp3000c01v1Output1Trap NOTIFICATION-TYPE
		OBJECTS { trapCounter, hvp3000c01v1Index, hvp3000c01v1Output1 }
		STATUS current
		DESCRIPTION
			"Input routed to output 1 Trap"
		::= { hvp3000c01v1Traps 3 }

		-- 1.3.6.1.4.1.10106.2.1.1.375001.3
		hvp3000c01v1Output2Trap NOTIFICATION-TYPE
		OBJECTS { trapCounter, hvp3000c01v1Index, hvp3000c01v1Output2 }
		STATUS current
		DESCRIPTION
			"Input routed to output 2 Trap"
		::= { hvp3000c01v1Traps 5 }

		-- 1.3.6.1.4.1.10106.2.1.1.375001.3
		hvp3000c01v1Output3Trap NOTIFICATION-TYPE
		OBJECTS { trapCounter, hvp3000c01v1Index, hvp3000c01v1Output3 }
		STATUS current
		DESCRIPTION
			"Input routed to output 3 Trap"
		::= { hvp3000c01v1Traps 7 }

		-- 1.3.6.1.4.1.10106.2.1.1.375001.3
		hvp3000c01v1Output4Trap NOTIFICATION-TYPE
		OBJECTS { trapCounter, hvp3000c01v1Index, hvp3000c01v1Output4 }
		STATUS current
		DESCRIPTION
			"Input routed to output 4 Trap"
		::= { hvp3000c01v1Traps 9 }

		-- 1.3.6.1.4.1.10106.2.1.1.375001.3
		hvp3000c01v1SyncFormatTrap NOTIFICATION-TYPE
		OBJECTS { trapCounter, hvp3000c01v1Index, hvp3000c01v1SyncFormat }
		STATUS current
		DESCRIPTION
			"Displays the reference's  input format Trap"
		::= { hvp3000c01v1Traps 21 }

		-- 1.3.6.1.4.1.10106.2.1.1.375001.3
		hvp3000c01v1Out1LckStatTrap NOTIFICATION-TYPE
		OBJECTS { trapCounter, hvp3000c01v1Index, hvp3000c01v1Out1LckStat }
		STATUS current
		DESCRIPTION
			"Output 1 lock status Trap"
		::= { hvp3000c01v1Traps 23 }

		-- 1.3.6.1.4.1.10106.2.1.1.375001.3
		hvp3000c01v1Out2LckStatTrap NOTIFICATION-TYPE
		OBJECTS { trapCounter, hvp3000c01v1Index, hvp3000c01v1Out2LckStat }
		STATUS current
		DESCRIPTION
			"Output 2 lock status Trap"
		::= { hvp3000c01v1Traps 25 }

		-- 1.3.6.1.4.1.10106.2.1.1.375001.3
		hvp3000c01v1Out3LckStatTrap NOTIFICATION-TYPE
		OBJECTS { trapCounter, hvp3000c01v1Index, hvp3000c01v1Out3LckStat }
		STATUS current
		DESCRIPTION
			"Output 3 lock status Trap"
		::= { hvp3000c01v1Traps 27 }

		-- 1.3.6.1.4.1.10106.2.1.1.375001.3
		hvp3000c01v1Out4LckStatTrap NOTIFICATION-TYPE
		OBJECTS { trapCounter, hvp3000c01v1Index, hvp3000c01v1Out4LckStat }
		STATUS current
		DESCRIPTION
			"Output 4 lock status Trap"
		::= { hvp3000c01v1Traps 29 }

		-- 1.3.6.1.4.1.10106.2.1.1.378901
		hdc3000c01v1Traps OBJECT IDENTIFIER ::= { albalaTraps 378901 }

		-- 1.3.6.1.4.1.10106.2.1.1.378901.3
		hdc3000c01v1AnaRefFmtTrap NOTIFICATION-TYPE
		OBJECTS { trapCounter, hdc3000c01v1Index, hdc3000c01v1AnaRefFmt }
		STATUS current
		DESCRIPTION
			"Analog reference input format Trap"
		::= { hdc3000c01v1Traps 9 }

		-- 1.3.6.1.4.1.10106.2.1.1.378901.3
		hdc3000c01v1ModeConvTrap NOTIFICATION-TYPE
		OBJECTS { trapCounter, hdc3000c01v1Index, hdc3000c01v1ModeConv }
		STATUS current
		DESCRIPTION
			"Conversion mode Trap"
		::= { hdc3000c01v1Traps 15 }

		-- 1.3.6.1.4.1.10106.2.1.1.378901.3
		hdc3000c01v1OutAfdTrap NOTIFICATION-TYPE
		OBJECTS { trapCounter, hdc3000c01v1Index, hdc3000c01v1OutAfd }
		STATUS current
		DESCRIPTION
			"Output active format description Trap"
		::= { hdc3000c01v1Traps 17 }

		-- 1.3.6.1.4.1.10106.2.1.1.378901.3
		hdc3000c01v1OutCfTrap NOTIFICATION-TYPE
		OBJECTS { trapCounter, hdc3000c01v1Index, hdc3000c01v1OutCf }
		STATUS current
		DESCRIPTION
			"Output coded frame Trap"
		::= { hdc3000c01v1Traps 19 }

		-- 1.3.6.1.4.1.10106.2.1.1.378901.3
		hdc3000c01v1InAfdExpctTrap NOTIFICATION-TYPE
		OBJECTS { trapCounter, hdc3000c01v1Index, hdc3000c01v1InAfdExpct }
		STATUS current
		DESCRIPTION
			"Input expected active format description Trap"
		::= { hdc3000c01v1Traps 21 }

		-- 1.3.6.1.4.1.10106.2.1.1.378901.3
		hdc3000c01v1InCfExpctTrap NOTIFICATION-TYPE
		OBJECTS { trapCounter, hdc3000c01v1Index, hdc3000c01v1InCfExpct }
		STATUS current
		DESCRIPTION
			"Input expected coded frame Trap"
		::= { hdc3000c01v1Traps 23 }

		-- 1.3.6.1.4.1.10106.2.1.1.378901.3
		hdc3000c01v1InAfdDetctTrap NOTIFICATION-TYPE
		OBJECTS { trapCounter, hdc3000c01v1Index, hdc3000c01v1InAfdDetct }
		STATUS current
		DESCRIPTION
			"Input detected AFD Trap"
		::= { hdc3000c01v1Traps 91 }

		-- 1.3.6.1.4.1.10106.2.1.1.378901.3
		hdc3000c01v1InCfDetctTrap NOTIFICATION-TYPE
		OBJECTS { trapCounter, hdc3000c01v1Index, hdc3000c01v1InCfDetct }
		STATUS current
		DESCRIPTION
			"Input detected coded frame Trap"
		::= { hdc3000c01v1Traps 93 }

		-- 1.3.6.1.4.1.10106.2.1.1.378901.3
		hdc3000c01v1InPhyFailTrap NOTIFICATION-TYPE
		OBJECTS { trapCounter, hdc3000c01v1Index, hdc3000c01v1InPhyFail }
		STATUS current
		DESCRIPTION
			"Absence fail Trap"
		::= { hdc3000c01v1Traps 95 }

		-- 1.3.6.1.4.1.10106.2.1.1.378901.3
		hdc3000c01v1InFmtFailTrap NOTIFICATION-TYPE
		OBJECTS { trapCounter, hdc3000c01v1Index, hdc3000c01v1InFmtFail }
		STATUS current
		DESCRIPTION
			"Format fail Trap"
		::= { hdc3000c01v1Traps 97 }

		-- 1.3.6.1.4.1.10106.2.1.1.378901.3
		hdc3000c01v1InIncFailTrap NOTIFICATION-TYPE
		OBJECTS { trapCounter, hdc3000c01v1Index, hdc3000c01v1InIncFail }
		STATUS current
		DESCRIPTION
			"Incompatible format fail Trap"
		::= { hdc3000c01v1Traps 99 }

		-- 1.3.6.1.4.1.10106.2.1.1.378901.3
		hdc3000c01v1InCrcFailTrap NOTIFICATION-TYPE
		OBJECTS { trapCounter, hdc3000c01v1Index, hdc3000c01v1InCrcFail }
		STATUS current
		DESCRIPTION
			"EDH/CRC fail Trap"
		::= { hdc3000c01v1Traps 103 }

		-- 1.3.6.1.4.1.10106.2.1.1.378901.3
		hdc3000c01v1PresAudG1FailTrap NOTIFICATION-TYPE
		OBJECTS { trapCounter, hdc3000c01v1Index, hdc3000c01v1PresAudG1Fail }
		STATUS current
		DESCRIPTION
			"Audio group 1 presence fail Trap"
		::= { hdc3000c01v1Traps 113 }

		-- 1.3.6.1.4.1.10106.2.1.1.378901.3
		hdc3000c01v1PresAudG2FailTrap NOTIFICATION-TYPE
		OBJECTS { trapCounter, hdc3000c01v1Index, hdc3000c01v1PresAudG2Fail }
		STATUS current
		DESCRIPTION
			"Audio group 2 presence fail Trap"
		::= { hdc3000c01v1Traps 115 }

		-- 1.3.6.1.4.1.10106.2.1.1.378901.3
		hdc3000c01v1PresAudG3FailTrap NOTIFICATION-TYPE
		OBJECTS { trapCounter, hdc3000c01v1Index, hdc3000c01v1PresAudG3Fail }
		STATUS current
		DESCRIPTION
			"Audio group 3 presence fail Trap"
		::= { hdc3000c01v1Traps 117 }

		-- 1.3.6.1.4.1.10106.2.1.1.378901.3
		hdc3000c01v1PresAudG4FailTrap NOTIFICATION-TYPE
		OBJECTS { trapCounter, hdc3000c01v1Index, hdc3000c01v1PresAudG4Fail }
		STATUS current
		DESCRIPTION
			"Audio group 4 presence fail Trap"
		::= { hdc3000c01v1Traps 119 }

		-- 1.3.6.1.4.1.10106.2.1.1.378901.3
		hdc3000c01v1RefFailTrap NOTIFICATION-TYPE
		OBJECTS { trapCounter, hdc3000c01v1Index, hdc3000c01v1RefFail }
		STATUS current
		DESCRIPTION
			"Analog reference absence fail Trap"
		::= { hdc3000c01v1Traps 121 }

		-- 1.3.6.1.4.1.10106.2.1.1.378901.3
		hdc3000c01v1RefFmtFailTrap NOTIFICATION-TYPE
		OBJECTS { trapCounter, hdc3000c01v1Index, hdc3000c01v1RefFmtFail }
		STATUS current
		DESCRIPTION
			"Analog reference format fail Trap"
		::= { hdc3000c01v1Traps 123 }

		-- 1.3.6.1.4.1.10106.2.1.1.378901.3
		hdc3000c01v1LockFailTrap NOTIFICATION-TYPE
		OBJECTS { trapCounter, hdc3000c01v1Index, hdc3000c01v1LockFail }
		STATUS current
		DESCRIPTION
			"Reference unlock fail Trap"
		::= { hdc3000c01v1Traps 125 }

		-- 1.3.6.1.4.1.10106.2.1.1.378901.3
		hdc3000c01v1AudPair0FailTrap NOTIFICATION-TYPE
		OBJECTS { trapCounter, hdc3000c01v1Index, hdc3000c01v1AudPair0Fail }
		STATUS current
		DESCRIPTION
			"Audio pair 0 fail Trap"
		::= { hdc3000c01v1Traps 127 }

		-- 1.3.6.1.4.1.10106.2.1.1.378901.3
		hdc3000c01v1AudPair1FailTrap NOTIFICATION-TYPE
		OBJECTS { trapCounter, hdc3000c01v1Index, hdc3000c01v1AudPair1Fail }
		STATUS current
		DESCRIPTION
			"Audio pair 1 fail Trap"
		::= { hdc3000c01v1Traps 129 }

		-- 1.3.6.1.4.1.10106.2.1.1.378901.3
		hdc3000c01v1AudPair2FailTrap NOTIFICATION-TYPE
		OBJECTS { trapCounter, hdc3000c01v1Index, hdc3000c01v1AudPair2Fail }
		STATUS current
		DESCRIPTION
			"Audio pair 2 fail Trap"
		::= { hdc3000c01v1Traps 131 }

		-- 1.3.6.1.4.1.10106.2.1.1.378901.3
		hdc3000c01v1AudPair3FailTrap NOTIFICATION-TYPE
		OBJECTS { trapCounter, hdc3000c01v1Index, hdc3000c01v1AudPair3Fail }
		STATUS current
		DESCRIPTION
			"Audio pair 3 fail Trap"
		::= { hdc3000c01v1Traps 133 }

		-- 1.3.6.1.4.1.10106.2.1.1.378901.3
		hdc3000c01v1AudPair4FailTrap NOTIFICATION-TYPE
		OBJECTS { trapCounter, hdc3000c01v1Index, hdc3000c01v1AudPair4Fail }
		STATUS current
		DESCRIPTION
			"Audio pair 4 fail Trap"
		::= { hdc3000c01v1Traps 135 }

		-- 1.3.6.1.4.1.10106.2.1.1.378901.3
		hdc3000c01v1AudPair5FailTrap NOTIFICATION-TYPE
		OBJECTS { trapCounter, hdc3000c01v1Index, hdc3000c01v1AudPair5Fail }
		STATUS current
		DESCRIPTION
			"Audio pair 5 fail Trap"
		::= { hdc3000c01v1Traps 137 }

		-- 1.3.6.1.4.1.10106.2.1.1.378901.3
		hdc3000c01v1AudPair6FailTrap NOTIFICATION-TYPE
		OBJECTS { trapCounter, hdc3000c01v1Index, hdc3000c01v1AudPair6Fail }
		STATUS current
		DESCRIPTION
			"Audio pair 6 fail Trap"
		::= { hdc3000c01v1Traps 139 }

		-- 1.3.6.1.4.1.10106.2.1.1.378901.3
		hdc3000c01v1AudPair7FailTrap NOTIFICATION-TYPE
		OBJECTS { trapCounter, hdc3000c01v1Index, hdc3000c01v1AudPair7Fail }
		STATUS current
		DESCRIPTION
			"Audio pair 7 fail Trap"
		::= { hdc3000c01v1Traps 141 }

		-- 1.3.6.1.4.1.10106.2.1.1.378901.3
		hdc3000c01v1InFormatTrap NOTIFICATION-TYPE
		OBJECTS { trapCounter, hdc3000c01v1Index, hdc3000c01v1InFormat }
		STATUS current
		DESCRIPTION
			"Input format Trap"
		::= { hdc3000c01v1Traps 143 }

		-- 1.3.6.1.4.1.10106.2.1.1.378901.3
		hdc3000c01v1RefFormatTrap NOTIFICATION-TYPE
		OBJECTS { trapCounter, hdc3000c01v1Index, hdc3000c01v1RefFormat }
		STATUS current
		DESCRIPTION
			"Reference format Trap"
		::= { hdc3000c01v1Traps 145 }

		-- 1.3.6.1.4.1.10106.2.1.1.379801
		hli3000c01v1Traps OBJECT IDENTIFIER ::= { albalaTraps 379801 }

		-- 1.3.6.1.4.1.10106.2.1.1.379801.3
		hli3000c01v1PgmInsLogo1Trap NOTIFICATION-TYPE
		OBJECTS { trapCounter, hli3000c01v1Index, hli3000c01v1PgmInsLogo1 }
		STATUS current
		DESCRIPTION
			"Allows inserting the logo in the program output Trap"
		::= { hli3000c01v1Traps 9 }

		-- 1.3.6.1.4.1.10106.2.1.1.379801.3
		hli3000c01v1PgmInsLogo2Trap NOTIFICATION-TYPE
		OBJECTS { trapCounter, hli3000c01v1Index, hli3000c01v1PgmInsLogo2 }
		STATUS current
		DESCRIPTION
			"Allows inserting the logo in the program output Trap"
		::= { hli3000c01v1Traps 11 }

		-- 1.3.6.1.4.1.10106.2.1.1.379801.3
		hli3000c01v1PgmInsLogo3Trap NOTIFICATION-TYPE
		OBJECTS { trapCounter, hli3000c01v1Index, hli3000c01v1PgmInsLogo3 }
		STATUS current
		DESCRIPTION
			"Allows inserting the logo in the program output Trap"
		::= { hli3000c01v1Traps 13 }

		-- 1.3.6.1.4.1.10106.2.1.1.379801.3
		hli3000c01v1PgmInsLogo4Trap NOTIFICATION-TYPE
		OBJECTS { trapCounter, hli3000c01v1Index, hli3000c01v1PgmInsLogo4 }
		STATUS current
		DESCRIPTION
			"Allows inserting the logo in the program output Trap"
		::= { hli3000c01v1Traps 15 }

		-- 1.3.6.1.4.1.10106.2.1.1.379801.3
		hli3000c01v1SelLogo1Trap NOTIFICATION-TYPE
		OBJECTS { trapCounter, hli3000c01v1Index, hli3000c01v1SelLogo1 }
		STATUS current
		DESCRIPTION
			"Allows selecting the logo to be inserted Trap"
		::= { hli3000c01v1Traps 25 }

		-- 1.3.6.1.4.1.10106.2.1.1.379801.3
		hli3000c01v1SelLogo2Trap NOTIFICATION-TYPE
		OBJECTS { trapCounter, hli3000c01v1Index, hli3000c01v1SelLogo2 }
		STATUS current
		DESCRIPTION
			"Allows selecting the logo to be inserted Trap"
		::= { hli3000c01v1Traps 27 }

		-- 1.3.6.1.4.1.10106.2.1.1.379801.3
		hli3000c01v1SelLogo3Trap NOTIFICATION-TYPE
		OBJECTS { trapCounter, hli3000c01v1Index, hli3000c01v1SelLogo3 }
		STATUS current
		DESCRIPTION
			"Allows selecting the logo to be inserted Trap"
		::= { hli3000c01v1Traps 29 }

		-- 1.3.6.1.4.1.10106.2.1.1.379801.3
		hli3000c01v1SelLogo4Trap NOTIFICATION-TYPE
		OBJECTS { trapCounter, hli3000c01v1Index, hli3000c01v1SelLogo4 }
		STATUS current
		DESCRIPTION
			"Allows selecting the logo to be inserted Trap"
		::= { hli3000c01v1Traps 31 }

		-- 1.3.6.1.4.1.10106.2.1.1.379801.3
		hli3000c01v1NoSignalTrap NOTIFICATION-TYPE
		OBJECTS { trapCounter, hli3000c01v1Index, hli3000c01v1NoSignal }
		STATUS current
		DESCRIPTION
			"There is no SDI signal or the format is not supported Trap"
		::= { hli3000c01v1Traps 51 }

		-- 1.3.6.1.4.1.10106.2.1.1.379801.3
		hli3000c01v1UnlockTrap NOTIFICATION-TYPE
		OBJECTS { trapCounter, hli3000c01v1Index, hli3000c01v1Unlock }
		STATUS current
		DESCRIPTION
			"Indicates signal unlock fail Trap"
		::= { hli3000c01v1Traps 53 }

		-- 1.3.6.1.4.1.10106.2.1.1.379801.3
		hli3000c01v1EdhErrorTrap NOTIFICATION-TYPE
		OBJECTS { trapCounter, hli3000c01v1Index, hli3000c01v1EdhError }
		STATUS current
		DESCRIPTION
			"There are EDH/CRC errors on SDI signal Trap"
		::= { hli3000c01v1Traps 55 }

		-- 1.3.6.1.4.1.10106.2.1.1.379801.3
		hli3000c01v1FormatTrap NOTIFICATION-TYPE
		OBJECTS { trapCounter, hli3000c01v1Index, hli3000c01v1Format }
		STATUS current
		DESCRIPTION
			"Indicates the SDI received signal format Trap"
		::= { hli3000c01v1Traps 57 }

		-- 1.3.6.1.4.1.10106.2.1.1.379801.3
		hli3000c01v1Gpi1Trap NOTIFICATION-TYPE
		OBJECTS { trapCounter, hli3000c01v1Index, hli3000c01v1Gpi1 }
		STATUS current
		DESCRIPTION
			"Transmitted GPI1 Trap"
		::= { hli3000c01v1Traps 59 }

		-- 1.3.6.1.4.1.10106.2.1.1.379801.3
		hli3000c01v1Gpi2Trap NOTIFICATION-TYPE
		OBJECTS { trapCounter, hli3000c01v1Index, hli3000c01v1Gpi2 }
		STATUS current
		DESCRIPTION
			"Transmitted GPI2 Trap"
		::= { hli3000c01v1Traps 61 }

		-- 1.3.6.1.4.1.10106.2.1.1.379801.3
		hli3000c01v1Gpi3Trap NOTIFICATION-TYPE
		OBJECTS { trapCounter, hli3000c01v1Index, hli3000c01v1Gpi3 }
		STATUS current
		DESCRIPTION
			"Transmitted GPI3 Trap"
		::= { hli3000c01v1Traps 63 }

		-- 1.3.6.1.4.1.10106.2.1.1.379801.3
		hli3000c01v1Gpi4Trap NOTIFICATION-TYPE
		OBJECTS { trapCounter, hli3000c01v1Index, hli3000c01v1Gpi4 }
		STATUS current
		DESCRIPTION
			"Transmitted GPI4 Trap"
		::= { hli3000c01v1Traps 65 }

		-- 1.3.6.1.4.1.10106.2.1.1.379801.3
		hli3000c01v1Gpi5Trap NOTIFICATION-TYPE
		OBJECTS { trapCounter, hli3000c01v1Index, hli3000c01v1Gpi5 }
		STATUS current
		DESCRIPTION
			"Transmitted GPI5 Trap"
		::= { hli3000c01v1Traps 67 }

		-- 1.3.6.1.4.1.10106.2.1.1.379801.3
		hli3000c01v1Gpi6Trap NOTIFICATION-TYPE
		OBJECTS { trapCounter, hli3000c01v1Index, hli3000c01v1Gpi6 }
		STATUS current
		DESCRIPTION
			"Transmitted GPI6 Trap"
		::= { hli3000c01v1Traps 69 }

		-- 1.3.6.1.4.1.10106.2.1.1.379801.3
		hli3000c01v1Gpi7Trap NOTIFICATION-TYPE
		OBJECTS { trapCounter, hli3000c01v1Index, hli3000c01v1Gpi7 }
		STATUS current
		DESCRIPTION
			"Transmitted GPI7 Trap"
		::= { hli3000c01v1Traps 71 }

		-- 1.3.6.1.4.1.10106.2.1.1.379801.3
		hli3000c01v1Gpi8Trap NOTIFICATION-TYPE
		OBJECTS { trapCounter, hli3000c01v1Index, hli3000c01v1Gpi8 }
		STATUS current
		DESCRIPTION
			"Transmitted GPI8 Trap"
		::= { hli3000c01v1Traps 73 }

		-- 1.3.6.1.4.1.10106.2.1.1.379802
		hli3000c01v2Traps OBJECT IDENTIFIER ::= { albalaTraps 379802 }

		-- 1.3.6.1.4.1.10106.2.1.1.379802.3
		hli3000c01v2ActivePresetTrap NOTIFICATION-TYPE
		OBJECTS { trapCounter, hli3000c01v2Index, hli3000c01v2ActivePreset }
		STATUS current
		DESCRIPTION
			"Shows the active preset Trap"
		::= { hli3000c01v2Traps 3 }

		-- 1.3.6.1.4.1.10106.2.1.1.379802.3
		hli3000c01v2PgmInsLogo1Trap NOTIFICATION-TYPE
		OBJECTS { trapCounter, hli3000c01v2Index, hli3000c01v2PgmInsLogo1 }
		STATUS current
		DESCRIPTION
			"Allows inserting the logo in the program output Trap"
		::= { hli3000c01v2Traps 9 }

		-- 1.3.6.1.4.1.10106.2.1.1.379802.3
		hli3000c01v2PgmInsLogo2Trap NOTIFICATION-TYPE
		OBJECTS { trapCounter, hli3000c01v2Index, hli3000c01v2PgmInsLogo2 }
		STATUS current
		DESCRIPTION
			"Allows inserting the logo in the program output Trap"
		::= { hli3000c01v2Traps 11 }

		-- 1.3.6.1.4.1.10106.2.1.1.379802.3
		hli3000c01v2PgmInsLogo3Trap NOTIFICATION-TYPE
		OBJECTS { trapCounter, hli3000c01v2Index, hli3000c01v2PgmInsLogo3 }
		STATUS current
		DESCRIPTION
			"Allows inserting the logo in the program output Trap"
		::= { hli3000c01v2Traps 13 }

		-- 1.3.6.1.4.1.10106.2.1.1.379802.3
		hli3000c01v2PgmInsLogo4Trap NOTIFICATION-TYPE
		OBJECTS { trapCounter, hli3000c01v2Index, hli3000c01v2PgmInsLogo4 }
		STATUS current
		DESCRIPTION
			"Allows inserting the logo in the program output Trap"
		::= { hli3000c01v2Traps 15 }

		-- 1.3.6.1.4.1.10106.2.1.1.379802.3
		hli3000c01v2SelLogo1Trap NOTIFICATION-TYPE
		OBJECTS { trapCounter, hli3000c01v2Index, hli3000c01v2SelLogo1 }
		STATUS current
		DESCRIPTION
			"Allows selecting the logo to be inserted Trap"
		::= { hli3000c01v2Traps 33 }

		-- 1.3.6.1.4.1.10106.2.1.1.379802.3
		hli3000c01v2SelLogo2Trap NOTIFICATION-TYPE
		OBJECTS { trapCounter, hli3000c01v2Index, hli3000c01v2SelLogo2 }
		STATUS current
		DESCRIPTION
			"Allows selecting the logo to be inserted Trap"
		::= { hli3000c01v2Traps 35 }

		-- 1.3.6.1.4.1.10106.2.1.1.379802.3
		hli3000c01v2SelLogo3Trap NOTIFICATION-TYPE
		OBJECTS { trapCounter, hli3000c01v2Index, hli3000c01v2SelLogo3 }
		STATUS current
		DESCRIPTION
			"Allows selecting the logo to be inserted Trap"
		::= { hli3000c01v2Traps 37 }

		-- 1.3.6.1.4.1.10106.2.1.1.379802.3
		hli3000c01v2SelLogo4Trap NOTIFICATION-TYPE
		OBJECTS { trapCounter, hli3000c01v2Index, hli3000c01v2SelLogo4 }
		STATUS current
		DESCRIPTION
			"Allows selecting the logo to be inserted Trap"
		::= { hli3000c01v2Traps 39 }

		-- 1.3.6.1.4.1.10106.2.1.1.379802.3
		hli3000c01v2NoSignalTrap NOTIFICATION-TYPE
		OBJECTS { trapCounter, hli3000c01v2Index, hli3000c01v2NoSignal }
		STATUS current
		DESCRIPTION
			"There is no SDI signal or the format is not supported Trap"
		::= { hli3000c01v2Traps 103 }

		-- 1.3.6.1.4.1.10106.2.1.1.379802.3
		hli3000c01v2UnlockTrap NOTIFICATION-TYPE
		OBJECTS { trapCounter, hli3000c01v2Index, hli3000c01v2Unlock }
		STATUS current
		DESCRIPTION
			"Indicates signal unlock fail Trap"
		::= { hli3000c01v2Traps 105 }

		-- 1.3.6.1.4.1.10106.2.1.1.379802.3
		hli3000c01v2EdhErrorTrap NOTIFICATION-TYPE
		OBJECTS { trapCounter, hli3000c01v2Index, hli3000c01v2EdhError }
		STATUS current
		DESCRIPTION
			"There are EDH/CRC errors on SDI signal Trap"
		::= { hli3000c01v2Traps 107 }

		-- 1.3.6.1.4.1.10106.2.1.1.379802.3
		hli3000c01v2FormatTrap NOTIFICATION-TYPE
		OBJECTS { trapCounter, hli3000c01v2Index, hli3000c01v2Format }
		STATUS current
		DESCRIPTION
			"Indicates the SDI received signal format Trap"
		::= { hli3000c01v2Traps 109 }

		-- 1.3.6.1.4.1.10106.2.1.1.379802.3
		hli3000c01v2Gpi1Trap NOTIFICATION-TYPE
		OBJECTS { trapCounter, hli3000c01v2Index, hli3000c01v2Gpi1 }
		STATUS current
		DESCRIPTION
			"Transmitted GPI1 Trap"
		::= { hli3000c01v2Traps 111 }

		-- 1.3.6.1.4.1.10106.2.1.1.379802.3
		hli3000c01v2Gpi2Trap NOTIFICATION-TYPE
		OBJECTS { trapCounter, hli3000c01v2Index, hli3000c01v2Gpi2 }
		STATUS current
		DESCRIPTION
			"Transmitted GPI2 Trap"
		::= { hli3000c01v2Traps 113 }

		-- 1.3.6.1.4.1.10106.2.1.1.379802.3
		hli3000c01v2Gpi3Trap NOTIFICATION-TYPE
		OBJECTS { trapCounter, hli3000c01v2Index, hli3000c01v2Gpi3 }
		STATUS current
		DESCRIPTION
			"Transmitted GPI3 Trap"
		::= { hli3000c01v2Traps 115 }

		-- 1.3.6.1.4.1.10106.2.1.1.379802.3
		hli3000c01v2Gpi4Trap NOTIFICATION-TYPE
		OBJECTS { trapCounter, hli3000c01v2Index, hli3000c01v2Gpi4 }
		STATUS current
		DESCRIPTION
			"Transmitted GPI4 Trap"
		::= { hli3000c01v2Traps 117 }

		-- 1.3.6.1.4.1.10106.2.1.1.379802.3
		hli3000c01v2Gpi5Trap NOTIFICATION-TYPE
		OBJECTS { trapCounter, hli3000c01v2Index, hli3000c01v2Gpi5 }
		STATUS current
		DESCRIPTION
			"Transmitted GPI5 Trap"
		::= { hli3000c01v2Traps 119 }

		-- 1.3.6.1.4.1.10106.2.1.1.379802.3
		hli3000c01v2Gpi6Trap NOTIFICATION-TYPE
		OBJECTS { trapCounter, hli3000c01v2Index, hli3000c01v2Gpi6 }
		STATUS current
		DESCRIPTION
			"Transmitted GPI6 Trap"
		::= { hli3000c01v2Traps 121 }

		-- 1.3.6.1.4.1.10106.2.1.1.379802.3
		hli3000c01v2Gpi7Trap NOTIFICATION-TYPE
		OBJECTS { trapCounter, hli3000c01v2Index, hli3000c01v2Gpi7 }
		STATUS current
		DESCRIPTION
			"Transmitted GPI7 Trap"
		::= { hli3000c01v2Traps 123 }

		-- 1.3.6.1.4.1.10106.2.1.1.379802.3
		hli3000c01v2Gpi8Trap NOTIFICATION-TYPE
		OBJECTS { trapCounter, hli3000c01v2Index, hli3000c01v2Gpi8 }
		STATUS current
		DESCRIPTION
			"Transmitted GPI8 Trap"
		::= { hli3000c01v2Traps 125 }

		-- 1.3.6.1.4.1.10106.2.1.1.380001
		eop0010c01v1Traps OBJECT IDENTIFIER ::= { albalaTraps 380001 }

		-- 1.3.6.1.4.1.10106.2.1.1.380001.3
		eop0010c01v1NoSigATrap NOTIFICATION-TYPE
		OBJECTS { trapCounter, eop0010c01v1Index, eop0010c01v1NoSigA }
		STATUS current
		DESCRIPTION
			"Input signal status Trap"
		::= { eop0010c01v1Traps 5 }

		-- 1.3.6.1.4.1.10106.2.1.1.380001.3
		eop0010c01v1UnlockATrap NOTIFICATION-TYPE
		OBJECTS { trapCounter, eop0010c01v1Index, eop0010c01v1UnlockA }
		STATUS current
		DESCRIPTION
			"Indicates signal unlock fail Trap"
		::= { eop0010c01v1Traps 7 }

		-- 1.3.6.1.4.1.10106.2.1.1.380001.3
		eop0010c01v1LFailATrap NOTIFICATION-TYPE
		OBJECTS { trapCounter, eop0010c01v1Index, eop0010c01v1LFailA }
		STATUS current
		DESCRIPTION
			"Indicates a fail in laser Trap"
		::= { eop0010c01v1Traps 9 }

		-- 1.3.6.1.4.1.10106.2.1.1.380001.3
		eop0010c01v1NoSigBTrap NOTIFICATION-TYPE
		OBJECTS { trapCounter, eop0010c01v1Index, eop0010c01v1NoSigB }
		STATUS current
		DESCRIPTION
			"Input signal status Trap"
		::= { eop0010c01v1Traps 11 }

		-- 1.3.6.1.4.1.10106.2.1.1.380001.3
		eop0010c01v1UnlockBTrap NOTIFICATION-TYPE
		OBJECTS { trapCounter, eop0010c01v1Index, eop0010c01v1UnlockB }
		STATUS current
		DESCRIPTION
			"Indicates signal unlock fail Trap"
		::= { eop0010c01v1Traps 13 }

		-- 1.3.6.1.4.1.10106.2.1.1.380001.3
		eop0010c01v1LFailBTrap NOTIFICATION-TYPE
		OBJECTS { trapCounter, eop0010c01v1Index, eop0010c01v1LFailB }
		STATUS current
		DESCRIPTION
			"Indicates a fail in laser Trap"
		::= { eop0010c01v1Traps 15 }

		-- 1.3.6.1.4.1.10106.2.1.1.382501
		hap3000c01v1Traps OBJECT IDENTIFIER ::= { albalaTraps 382501 }

		-- 1.3.6.1.4.1.10106.2.1.1.382501.3
		hap3000c01v1NoSigTrap NOTIFICATION-TYPE
		OBJECTS { trapCounter, hap3000c01v1Index, hap3000c01v1NoSig }
		STATUS current
		DESCRIPTION
			"No SDI signal fail Trap"
		::= { hap3000c01v1Traps 157 }

		-- 1.3.6.1.4.1.10106.2.1.1.382501.3
		hap3000c01v1UnlockTrap NOTIFICATION-TYPE
		OBJECTS { trapCounter, hap3000c01v1Index, hap3000c01v1Unlock }
		STATUS current
		DESCRIPTION
			"Unlock fail Trap"
		::= { hap3000c01v1Traps 159 }

		-- 1.3.6.1.4.1.10106.2.1.1.382501.3
		hap3000c01v1EdhCrcTrap NOTIFICATION-TYPE
		OBJECTS { trapCounter, hap3000c01v1Index, hap3000c01v1EdhCrc }
		STATUS current
		DESCRIPTION
			"EDH/CRC errors Trap"
		::= { hap3000c01v1Traps 161 }

		-- 1.3.6.1.4.1.10106.2.1.1.382501.3
		hap3000c01v1NoRefTrap NOTIFICATION-TYPE
		OBJECTS { trapCounter, hap3000c01v1Index, hap3000c01v1NoRef }
		STATUS current
		DESCRIPTION
			"No reference signal fail Trap"
		::= { hap3000c01v1Traps 163 }

		-- 1.3.6.1.4.1.10106.2.1.1.382501.3
		hap3000c01v1RefUnlckTrap NOTIFICATION-TYPE
		OBJECTS { trapCounter, hap3000c01v1Index, hap3000c01v1RefUnlck }
		STATUS current
		DESCRIPTION
			"Reference input unlock fail Trap"
		::= { hap3000c01v1Traps 165 }

		-- 1.3.6.1.4.1.10106.2.1.1.382501.3
		hap3000c01v1AudioFailTrap NOTIFICATION-TYPE
		OBJECTS { trapCounter, hap3000c01v1Index, hap3000c01v1AudioFail }
		STATUS current
		DESCRIPTION
			"Audio fail Trap"
		::= { hap3000c01v1Traps 167 }

		-- 1.3.6.1.4.1.10106.2.1.1.382502
		hap3000c01v2Traps OBJECT IDENTIFIER ::= { albalaTraps 382502 }

		-- 1.3.6.1.4.1.10106.2.1.1.382502.3
		hap3000c01v2NoSigTrap NOTIFICATION-TYPE
		OBJECTS { trapCounter, hap3000c01v2Index, hap3000c01v2NoSig }
		STATUS current
		DESCRIPTION
			"No SDI signal fail Trap"
		::= { hap3000c01v2Traps 157 }

		-- 1.3.6.1.4.1.10106.2.1.1.382502.3
		hap3000c01v2UnlockTrap NOTIFICATION-TYPE
		OBJECTS { trapCounter, hap3000c01v2Index, hap3000c01v2Unlock }
		STATUS current
		DESCRIPTION
			"Unlock fail Trap"
		::= { hap3000c01v2Traps 159 }

		-- 1.3.6.1.4.1.10106.2.1.1.382502.3
		hap3000c01v2EdhCrcTrap NOTIFICATION-TYPE
		OBJECTS { trapCounter, hap3000c01v2Index, hap3000c01v2EdhCrc }
		STATUS current
		DESCRIPTION
			"EDH/CRC errors Trap"
		::= { hap3000c01v2Traps 161 }

		-- 1.3.6.1.4.1.10106.2.1.1.382502.3
		hap3000c01v2NoRefTrap NOTIFICATION-TYPE
		OBJECTS { trapCounter, hap3000c01v2Index, hap3000c01v2NoRef }
		STATUS current
		DESCRIPTION
			"No reference signal fail Trap"
		::= { hap3000c01v2Traps 163 }

		-- 1.3.6.1.4.1.10106.2.1.1.382502.3
		hap3000c01v2RefUnlckTrap NOTIFICATION-TYPE
		OBJECTS { trapCounter, hap3000c01v2Index, hap3000c01v2RefUnlck }
		STATUS current
		DESCRIPTION
			"Reference input unlock fail Trap"
		::= { hap3000c01v2Traps 165 }

		-- 1.3.6.1.4.1.10106.2.1.1.382502.3
		hap3000c01v2AudioFailTrap NOTIFICATION-TYPE
		OBJECTS { trapCounter, hap3000c01v2Index, hap3000c01v2AudioFail }
		STATUS current
		DESCRIPTION
			"Audio fail Trap"
		::= { hap3000c01v2Traps 167 }

		-- 1.3.6.1.4.1.10106.2.1.1.386801
		psu3300c01v1Traps OBJECT IDENTIFIER ::= { albalaTraps 386801 }

		-- 1.3.6.1.4.1.10106.2.1.1.386801.3
		psu3300c01v1PowerOffTrap NOTIFICATION-TYPE
		OBJECTS { trapCounter, psu3300c01v1Index, psu3300c01v1PowerOff }
		STATUS current
		DESCRIPTION
			"Indicates the power supply status Trap"
		::= { psu3300c01v1Traps 3 }

		-- 1.3.6.1.4.1.10106.2.1.1.386801.3
		psu3300c01v1TempWarningTrap NOTIFICATION-TYPE
		OBJECTS { trapCounter, psu3300c01v1Index, psu3300c01v1TempWarning }
		STATUS current
		DESCRIPTION
			"Indicates that actual temperature is over expected range Trap"
		::= { psu3300c01v1Traps 5 }

		-- 1.3.6.1.4.1.10106.2.1.1.386801.3
		psu3300c01v1TempFailTrap NOTIFICATION-TYPE
		OBJECTS { trapCounter, psu3300c01v1Index, psu3300c01v1TempFail }
		STATUS current
		DESCRIPTION
			"Indicates that actual temperature is over recommended range Trap"
		::= { psu3300c01v1Traps 7 }

		-- 1.3.6.1.4.1.10106.2.1.1.388901
		psu3300c02v1Traps OBJECT IDENTIFIER ::= { albalaTraps 388901 }

		-- 1.3.6.1.4.1.10106.2.1.1.388901.3
		psu3300c02v1PowerOffTrap NOTIFICATION-TYPE
		OBJECTS { trapCounter, psu3300c02v1Index, psu3300c02v1PowerOff }
		STATUS current
		DESCRIPTION
			"Indicates the power supply status Trap"
		::= { psu3300c02v1Traps 3 }

		-- 1.3.6.1.4.1.10106.2.1.1.388901.3
		psu3300c02v1TempWarningTrap NOTIFICATION-TYPE
		OBJECTS { trapCounter, psu3300c02v1Index, psu3300c02v1TempWarning }
		STATUS current
		DESCRIPTION
			"Indicates that actual temperature is over expected range Trap"
		::= { psu3300c02v1Traps 5 }

		-- 1.3.6.1.4.1.10106.2.1.1.388901.3
		psu3300c02v1TempFailTrap NOTIFICATION-TYPE
		OBJECTS { trapCounter, psu3300c02v1Index, psu3300c02v1TempFail }
		STATUS current
		DESCRIPTION
			"Indicates that actual temperature is over recommended range Trap"
		::= { psu3300c02v1Traps 7 }

		-- 1.3.6.1.4.1.10106.2.1.1.389201
		psu3301c01v1Traps OBJECT IDENTIFIER ::= { albalaTraps 389201 }

		-- 1.3.6.1.4.1.10106.2.1.1.389201.3
		psu3301c01v1PowerOffTrap NOTIFICATION-TYPE
		OBJECTS { trapCounter, psu3301c01v1Index, psu3301c01v1PowerOff }
		STATUS current
		DESCRIPTION
			"Indicates the power supply status Trap"
		::= { psu3301c01v1Traps 3 }

		-- 1.3.6.1.4.1.10106.2.1.1.389201.3
		psu3301c01v1TempWarningTrap NOTIFICATION-TYPE
		OBJECTS { trapCounter, psu3301c01v1Index, psu3301c01v1TempWarning }
		STATUS current
		DESCRIPTION
			"Indicates that actual temperature is over expected range Trap"
		::= { psu3301c01v1Traps 5 }

		-- 1.3.6.1.4.1.10106.2.1.1.389201.3
		psu3301c01v1TempFailTrap NOTIFICATION-TYPE
		OBJECTS { trapCounter, psu3301c01v1Index, psu3301c01v1TempFail }
		STATUS current
		DESCRIPTION
			"Indicates that actual temperature is over recommended range Trap"
		::= { psu3301c01v1Traps 7 }

		-- 1.3.6.1.4.1.10106.2.1.1.389501
		psu3301c03v1Traps OBJECT IDENTIFIER ::= { albalaTraps 389501 }

		-- 1.3.6.1.4.1.10106.2.1.1.389501.3
		psu3301c03v1PowerOffTrap NOTIFICATION-TYPE
		OBJECTS { trapCounter, psu3301c03v1Index, psu3301c03v1PowerOff }
		STATUS current
		DESCRIPTION
			"Indicates the power supply status Trap"
		::= { psu3301c03v1Traps 3 }

		-- 1.3.6.1.4.1.10106.2.1.1.389501.3
		psu3301c03v1TempWarningTrap NOTIFICATION-TYPE
		OBJECTS { trapCounter, psu3301c03v1Index, psu3301c03v1TempWarning }
		STATUS current
		DESCRIPTION
			"Indicates that actual temperature is over expected range Trap"
		::= { psu3301c03v1Traps 5 }

		-- 1.3.6.1.4.1.10106.2.1.1.389501.3
		psu3301c03v1TempFailTrap NOTIFICATION-TYPE
		OBJECTS { trapCounter, psu3301c03v1Index, psu3301c03v1TempFail }
		STATUS current
		DESCRIPTION
			"Indicates that actual temperature is over recommended range Trap"
		::= { psu3301c03v1Traps 7 }

		-- 1.3.6.1.4.1.10106.2.1.1.392001
		avd3001c02v1Traps OBJECT IDENTIFIER ::= { albalaTraps 392001 }

		-- 1.3.6.1.4.1.10106.2.1.1.392001.3
		avd3001c02v1NoSigATrap NOTIFICATION-TYPE
		OBJECTS { trapCounter, avd3001c02v1Index, avd3001c02v1NoSigA }
		STATUS current
		DESCRIPTION
			"Input signal status Trap"
		::= { avd3001c02v1Traps 7 }

		-- 1.3.6.1.4.1.10106.2.1.1.392001.3
		avd3001c02v1UnlockATrap NOTIFICATION-TYPE
		OBJECTS { trapCounter, avd3001c02v1Index, avd3001c02v1UnlockA }
		STATUS current
		DESCRIPTION
			"Indicates signal unlock fail Trap"
		::= { avd3001c02v1Traps 9 }

		-- 1.3.6.1.4.1.10106.2.1.1.392001.3
		avd3001c02v1SyncFormatTrap NOTIFICATION-TYPE
		OBJECTS { trapCounter, avd3001c02v1Index, avd3001c02v1SyncFormat }
		STATUS current
		DESCRIPTION
			"Displays signal's  input format Trap"
		::= { avd3001c02v1Traps 11 }

		-- 1.3.6.1.4.1.10106.2.1.1.393601
		avd3001c01v1Traps OBJECT IDENTIFIER ::= { albalaTraps 393601 }

		-- 1.3.6.1.4.1.10106.2.1.1.393601.3
		avd3001c01v1NoSigATrap NOTIFICATION-TYPE
		OBJECTS { trapCounter, avd3001c01v1Index, avd3001c01v1NoSigA }
		STATUS current
		DESCRIPTION
			"Input signal status Trap"
		::= { avd3001c01v1Traps 7 }

		-- 1.3.6.1.4.1.10106.2.1.1.393601.3
		avd3001c01v1UnlockATrap NOTIFICATION-TYPE
		OBJECTS { trapCounter, avd3001c01v1Index, avd3001c01v1UnlockA }
		STATUS current
		DESCRIPTION
			"Indicates signal unlock fail Trap"
		::= { avd3001c01v1Traps 9 }

		-- 1.3.6.1.4.1.10106.2.1.1.393601.3
		avd3001c01v1SyncFormatTrap NOTIFICATION-TYPE
		OBJECTS { trapCounter, avd3001c01v1Index, avd3001c01v1SyncFormat }
		STATUS current
		DESCRIPTION
			"Displays signal's  input format Trap"
		::= { avd3001c01v1Traps 11 }

		-- 1.3.6.1.4.1.10106.2.1.1.393701
		avd3001c03v1Traps OBJECT IDENTIFIER ::= { albalaTraps 393701 }

		-- 1.3.6.1.4.1.10106.2.1.1.393701.3
		avd3001c03v1NoSigATrap NOTIFICATION-TYPE
		OBJECTS { trapCounter, avd3001c03v1Index, avd3001c03v1NoSigA }
		STATUS current
		DESCRIPTION
			"Input signal status Trap"
		::= { avd3001c03v1Traps 3 }

		-- 1.3.6.1.4.1.10106.2.1.1.393701.3
		avd3001c03v1UnlockATrap NOTIFICATION-TYPE
		OBJECTS { trapCounter, avd3001c03v1Index, avd3001c03v1UnlockA }
		STATUS current
		DESCRIPTION
			"Indicates signal unlock fail Trap"
		::= { avd3001c03v1Traps 5 }

		-- 1.3.6.1.4.1.10106.2.1.1.393701.3
		avd3001c03v1SyncFormatTrap NOTIFICATION-TYPE
		OBJECTS { trapCounter, avd3001c03v1Index, avd3001c03v1SyncFormat }
		STATUS current
		DESCRIPTION
			"Displays signal's  input format Trap"
		::= { avd3001c03v1Traps 7 }

		-- 1.3.6.1.4.1.10106.2.1.1.399601
		vgp3000c01v1Traps OBJECT IDENTIFIER ::= { albalaTraps 399601 }

		-- 1.3.6.1.4.1.10106.2.1.1.399601.3
		vgp3000c01v1Gpi1Trap NOTIFICATION-TYPE
		OBJECTS { trapCounter, vgp3000c01v1Index, vgp3000c01v1Gpi1 }
		STATUS current
		DESCRIPTION
			"Transmitted GPI1 Trap"
		::= { vgp3000c01v1Traps 581 }

		-- 1.3.6.1.4.1.10106.2.1.1.399601.3
		vgp3000c01v1Gpi2Trap NOTIFICATION-TYPE
		OBJECTS { trapCounter, vgp3000c01v1Index, vgp3000c01v1Gpi2 }
		STATUS current
		DESCRIPTION
			"Transmitted GPI2 Trap"
		::= { vgp3000c01v1Traps 583 }

		-- 1.3.6.1.4.1.10106.2.1.1.399601.3
		vgp3000c01v1Gpi3Trap NOTIFICATION-TYPE
		OBJECTS { trapCounter, vgp3000c01v1Index, vgp3000c01v1Gpi3 }
		STATUS current
		DESCRIPTION
			"Transmitted GPI3 Trap"
		::= { vgp3000c01v1Traps 585 }

		-- 1.3.6.1.4.1.10106.2.1.1.399601.3
		vgp3000c01v1Gpi4Trap NOTIFICATION-TYPE
		OBJECTS { trapCounter, vgp3000c01v1Index, vgp3000c01v1Gpi4 }
		STATUS current
		DESCRIPTION
			"Transmitted GPI4 Trap"
		::= { vgp3000c01v1Traps 587 }

		-- 1.3.6.1.4.1.10106.2.1.1.399601.3
		vgp3000c01v1Gpi5Trap NOTIFICATION-TYPE
		OBJECTS { trapCounter, vgp3000c01v1Index, vgp3000c01v1Gpi5 }
		STATUS current
		DESCRIPTION
			"Transmitted GPI5 Trap"
		::= { vgp3000c01v1Traps 589 }

		-- 1.3.6.1.4.1.10106.2.1.1.399601.3
		vgp3000c01v1Gpi6Trap NOTIFICATION-TYPE
		OBJECTS { trapCounter, vgp3000c01v1Index, vgp3000c01v1Gpi6 }
		STATUS current
		DESCRIPTION
			"Transmitted GPI6 Trap"
		::= { vgp3000c01v1Traps 591 }

		-- 1.3.6.1.4.1.10106.2.1.1.399601.3
		vgp3000c01v1Gpi7Trap NOTIFICATION-TYPE
		OBJECTS { trapCounter, vgp3000c01v1Index, vgp3000c01v1Gpi7 }
		STATUS current
		DESCRIPTION
			"Transmitted GPI7 Trap"
		::= { vgp3000c01v1Traps 593 }

		-- 1.3.6.1.4.1.10106.2.1.1.399601.3
		vgp3000c01v1Gpi8Trap NOTIFICATION-TYPE
		OBJECTS { trapCounter, vgp3000c01v1Index, vgp3000c01v1Gpi8 }
		STATUS current
		DESCRIPTION
			"Transmitted GPI8 Trap"
		::= { vgp3000c01v1Traps 595 }

		-- 1.3.6.1.4.1.10106.2.1.1.399601.3
		vgp3000c01v1Gpo1Trap NOTIFICATION-TYPE
		OBJECTS { trapCounter, vgp3000c01v1Index, vgp3000c01v1Gpo1 }
		STATUS current
		DESCRIPTION
			"Received GPO1 Trap"
		::= { vgp3000c01v1Traps 597 }

		-- 1.3.6.1.4.1.10106.2.1.1.399601.3
		vgp3000c01v1Gpo2Trap NOTIFICATION-TYPE
		OBJECTS { trapCounter, vgp3000c01v1Index, vgp3000c01v1Gpo2 }
		STATUS current
		DESCRIPTION
			"Received GPO2 Trap"
		::= { vgp3000c01v1Traps 599 }

		-- 1.3.6.1.4.1.10106.2.1.1.399601.3
		vgp3000c01v1Gpo3Trap NOTIFICATION-TYPE
		OBJECTS { trapCounter, vgp3000c01v1Index, vgp3000c01v1Gpo3 }
		STATUS current
		DESCRIPTION
			"Received GPO3 Trap"
		::= { vgp3000c01v1Traps 601 }

		-- 1.3.6.1.4.1.10106.2.1.1.399601.3
		vgp3000c01v1Gpo4Trap NOTIFICATION-TYPE
		OBJECTS { trapCounter, vgp3000c01v1Index, vgp3000c01v1Gpo4 }
		STATUS current
		DESCRIPTION
			"Received GPO4 Trap"
		::= { vgp3000c01v1Traps 603 }

		-- 1.3.6.1.4.1.10106.2.1.1.399601.3
		vgp3000c01v1Gpo5Trap NOTIFICATION-TYPE
		OBJECTS { trapCounter, vgp3000c01v1Index, vgp3000c01v1Gpo5 }
		STATUS current
		DESCRIPTION
			"Received GPO5 Trap"
		::= { vgp3000c01v1Traps 605 }

		-- 1.3.6.1.4.1.10106.2.1.1.399601.3
		vgp3000c01v1Gpo6Trap NOTIFICATION-TYPE
		OBJECTS { trapCounter, vgp3000c01v1Index, vgp3000c01v1Gpo6 }
		STATUS current
		DESCRIPTION
			"Received GPO6 Trap"
		::= { vgp3000c01v1Traps 607 }

		-- 1.3.6.1.4.1.10106.2.1.1.399601.3
		vgp3000c01v1Gpo7Trap NOTIFICATION-TYPE
		OBJECTS { trapCounter, vgp3000c01v1Index, vgp3000c01v1Gpo7 }
		STATUS current
		DESCRIPTION
			"Received GPO7 Trap"
		::= { vgp3000c01v1Traps 609 }

		-- 1.3.6.1.4.1.10106.2.1.1.399601.3
		vgp3000c01v1Gpo8Trap NOTIFICATION-TYPE
		OBJECTS { trapCounter, vgp3000c01v1Index, vgp3000c01v1Gpo8 }
		STATUS current
		DESCRIPTION
			"Received GPO8 Trap"
		::= { vgp3000c01v1Traps 611 }

		-- 1.3.6.1.4.1.10106.2.1.1.403001
		ham3000c01v1Traps OBJECT IDENTIFIER ::= { albalaTraps 403001 }

		-- 1.3.6.1.4.1.10106.2.1.1.403001.3
		ham3000c01v1NoSignalMainTrap NOTIFICATION-TYPE
		OBJECTS { trapCounter, ham3000c01v1Index, ham3000c01v1NoSignalMain }
		STATUS current
		DESCRIPTION
			"There is no SDI signal or the format is not supported in PGM IN Trap"
		::= { ham3000c01v1Traps 305 }

		-- 1.3.6.1.4.1.10106.2.1.1.403001.3
		ham3000c01v1UnlockMainTrap NOTIFICATION-TYPE
		OBJECTS { trapCounter, ham3000c01v1Index, ham3000c01v1UnlockMain }
		STATUS current
		DESCRIPTION
			"Indicates signal unlock fail Trap"
		::= { ham3000c01v1Traps 307 }

		-- 1.3.6.1.4.1.10106.2.1.1.403001.3
		ham3000c01v1EdhErrorMainTrap NOTIFICATION-TYPE
		OBJECTS { trapCounter, ham3000c01v1Index, ham3000c01v1EdhErrorMain }
		STATUS current
		DESCRIPTION
			"There are EDH/CRC errors on PGM IN Trap"
		::= { ham3000c01v1Traps 309 }

		-- 1.3.6.1.4.1.10106.2.1.1.403001.3
		ham3000c01v1RefAbsentTrap NOTIFICATION-TYPE
		OBJECTS { trapCounter, ham3000c01v1Index, ham3000c01v1RefAbsent }
		STATUS current
		DESCRIPTION
			"There is no reference signal Trap"
		::= { ham3000c01v1Traps 317 }

		-- 1.3.6.1.4.1.10106.2.1.1.403001.3
		ham3000c01v1RefUnlockTrap NOTIFICATION-TYPE
		OBJECTS { trapCounter, ham3000c01v1Index, ham3000c01v1RefUnlock }
		STATUS current
		DESCRIPTION
			"Reference input unlock fail Trap"
		::= { ham3000c01v1Traps 319 }

		-- 1.3.6.1.4.1.10106.2.1.1.403001.3
		ham3000c01v1Gr1MainPresTrap NOTIFICATION-TYPE
		OBJECTS { trapCounter, ham3000c01v1Index, ham3000c01v1Gr1MainPres }
		STATUS current
		DESCRIPTION
			"Indicates group 1 presence in PGM IN Trap"
		::= { ham3000c01v1Traps 331 }

		-- 1.3.6.1.4.1.10106.2.1.1.403001.3
		ham3000c01v1Gr2MainPresTrap NOTIFICATION-TYPE
		OBJECTS { trapCounter, ham3000c01v1Index, ham3000c01v1Gr2MainPres }
		STATUS current
		DESCRIPTION
			"Indicates group 2 presence in PGM IN Trap"
		::= { ham3000c01v1Traps 333 }

		-- 1.3.6.1.4.1.10106.2.1.1.403001.3
		ham3000c01v1Gr3MainPresTrap NOTIFICATION-TYPE
		OBJECTS { trapCounter, ham3000c01v1Index, ham3000c01v1Gr3MainPres }
		STATUS current
		DESCRIPTION
			"Indicates group 3 presence in PGM IN Trap"
		::= { ham3000c01v1Traps 335 }

		-- 1.3.6.1.4.1.10106.2.1.1.403001.3
		ham3000c01v1Gr4MainPresTrap NOTIFICATION-TYPE
		OBJECTS { trapCounter, ham3000c01v1Index, ham3000c01v1Gr4MainPres }
		STATUS current
		DESCRIPTION
			"Indicates group 4 presence in PGM IN Trap"
		::= { ham3000c01v1Traps 337 }

		-- 1.3.6.1.4.1.10106.2.1.1.403001.3
		ham3000c01v1AudStatMainTrap NOTIFICATION-TYPE
		OBJECTS { trapCounter, ham3000c01v1Index, ham3000c01v1AudStatMain }
		STATUS current
		DESCRIPTION
			"Indicates audio fail in audio channels embedded in PGM IN Trap"
		::= { ham3000c01v1Traps 355 }

		-- 1.3.6.1.4.1.10106.2.1.1.403001.3
		ham3000c01v1AudStatAuxTrap NOTIFICATION-TYPE
		OBJECTS { trapCounter, ham3000c01v1Index, ham3000c01v1AudStatAux }
		STATUS current
		DESCRIPTION
			"Indicates audio fail in audio channels embedded in AUX IN Trap"
		::= { ham3000c01v1Traps 357 }

		-- 1.3.6.1.4.1.10106.2.1.1.403001.3
		ham3000c01v1AudStatAes1Trap NOTIFICATION-TYPE
		OBJECTS { trapCounter, ham3000c01v1Index, ham3000c01v1AudStatAes1 }
		STATUS current
		DESCRIPTION
			"Indicates audio fail in AES1 input Trap"
		::= { ham3000c01v1Traps 359 }

		-- 1.3.6.1.4.1.10106.2.1.1.403001.3
		ham3000c01v1AudStatAes2Trap NOTIFICATION-TYPE
		OBJECTS { trapCounter, ham3000c01v1Index, ham3000c01v1AudStatAes2 }
		STATUS current
		DESCRIPTION
			"Indicates audio fail in AES2 input Trap"
		::= { ham3000c01v1Traps 361 }

		-- 1.3.6.1.4.1.10106.2.1.1.403001.3
		ham3000c01v1OvldPgmOutTrap NOTIFICATION-TYPE
		OBJECTS { trapCounter, ham3000c01v1Index, ham3000c01v1OvldPgmOut }
		STATUS current
		DESCRIPTION
			"Indicates audio overload in SDI output PGM OUT Trap"
		::= { ham3000c01v1Traps 363 }

		-- 1.3.6.1.4.1.10106.2.1.1.403001.3
		ham3000c01v1OvldAes1OutTrap NOTIFICATION-TYPE
		OBJECTS { trapCounter, ham3000c01v1Index, ham3000c01v1OvldAes1Out }
		STATUS current
		DESCRIPTION
			"Indicates audio overload in AES1 OUT Trap"
		::= { ham3000c01v1Traps 365 }

		-- 1.3.6.1.4.1.10106.2.1.1.403001.3
		ham3000c01v1OvldAes2OutTrap NOTIFICATION-TYPE
		OBJECTS { trapCounter, ham3000c01v1Index, ham3000c01v1OvldAes2Out }
		STATUS current
		DESCRIPTION
			"Indicates audio overload in AES2 OUT Trap"
		::= { ham3000c01v1Traps 367 }

		-- 1.3.6.1.4.1.10106.2.1.1.403001.3
		ham3000c01v1SilPgmOutTrap NOTIFICATION-TYPE
		OBJECTS { trapCounter, ham3000c01v1Index, ham3000c01v1SilPgmOut }
		STATUS current
		DESCRIPTION
			"Indicates audio silence in SDI_PGM_OUT Trap"
		::= { ham3000c01v1Traps 369 }

		-- 1.3.6.1.4.1.10106.2.1.1.403001.3
		ham3000c01v1SilAes1OutTrap NOTIFICATION-TYPE
		OBJECTS { trapCounter, ham3000c01v1Index, ham3000c01v1SilAes1Out }
		STATUS current
		DESCRIPTION
			"Indicates audio silence in AES1_OUT Trap"
		::= { ham3000c01v1Traps 371 }

		-- 1.3.6.1.4.1.10106.2.1.1.403001.3
		ham3000c01v1SilAes2OutTrap NOTIFICATION-TYPE
		OBJECTS { trapCounter, ham3000c01v1Index, ham3000c01v1SilAes2Out }
		STATUS current
		DESCRIPTION
			"Indicates audio silence in AES2_OUT Trap"
		::= { ham3000c01v1Traps 373 }

		-- 1.3.6.1.4.1.10106.2.1.1.404701
		agw3000c01v1Traps OBJECT IDENTIFIER ::= { albalaTraps 404701 }

		-- 1.3.6.1.4.1.10106.2.1.1.404701.3
		agw3000c01v1ModeTrap NOTIFICATION-TYPE
		OBJECTS { trapCounter, agw3000c01v1Index, agw3000c01v1Mode }
		STATUS current
		DESCRIPTION
			"Allows selecting the switching mode Trap"
		::= { agw3000c01v1Traps 3 }

		-- 1.3.6.1.4.1.10106.2.1.1.404701.3
		agw3000c01v1DvbTModeTrap NOTIFICATION-TYPE
		OBJECTS { trapCounter, agw3000c01v1Index, agw3000c01v1DvbTMode }
		STATUS current
		DESCRIPTION
			"Selects DVB-T mode. Seamless operation is only possible in DVB-T mode Trap"
		::= { agw3000c01v1Traps 5 }

		-- 1.3.6.1.4.1.10106.2.1.1.404701.3
		agw3000c01v1AsiOut1InTrap NOTIFICATION-TYPE
		OBJECTS { trapCounter, agw3000c01v1Index, agw3000c01v1AsiOut1In }
		STATUS current
		DESCRIPTION
			"ASI OUT 2 - Selected input Trap"
		::= { agw3000c01v1Traps 27 }

		-- 1.3.6.1.4.1.10106.2.1.1.404701.3
		agw3000c01v1AsiOut2InTrap NOTIFICATION-TYPE
		OBJECTS { trapCounter, agw3000c01v1Index, agw3000c01v1AsiOut2In }
		STATUS current
		DESCRIPTION
			"ASI OUT 1 - Selected input Trap"
		::= { agw3000c01v1Traps 29 }

		-- 1.3.6.1.4.1.10106.2.1.1.404701.3
		agw3000c01v1IpOut1InTrap NOTIFICATION-TYPE
		OBJECTS { trapCounter, agw3000c01v1Index, agw3000c01v1IpOut1In }
		STATUS current
		DESCRIPTION
			"IP OUT 1 - Selected input Trap"
		::= { agw3000c01v1Traps 31 }

		-- 1.3.6.1.4.1.10106.2.1.1.404701.3
		agw3000c01v1IpOut2InTrap NOTIFICATION-TYPE
		OBJECTS { trapCounter, agw3000c01v1Index, agw3000c01v1IpOut2In }
		STATUS current
		DESCRIPTION
			"IP OUT 2 - Selected input Trap"
		::= { agw3000c01v1Traps 33 }

		-- 1.3.6.1.4.1.10106.2.1.1.404701.3
		agw3000c01v1AsiIn1FailTrap NOTIFICATION-TYPE
		OBJECTS { trapCounter, agw3000c01v1Index, agw3000c01v1AsiIn1Fail }
		STATUS current
		DESCRIPTION
			"ASI IN 1 fail status Trap"
		::= { agw3000c01v1Traps 345 }

		-- 1.3.6.1.4.1.10106.2.1.1.404701.3
		agw3000c01v1ExAsiIn1FailTrap NOTIFICATION-TYPE
		OBJECTS { trapCounter, agw3000c01v1Index, agw3000c01v1ExAsiIn1Fail }
		STATUS current
		DESCRIPTION
			"ASI IN 1 external input fail status Trap"
		::= { agw3000c01v1Traps 347 }

		-- 1.3.6.1.4.1.10106.2.1.1.404701.3
		agw3000c01v1AsiIn2FailTrap NOTIFICATION-TYPE
		OBJECTS { trapCounter, agw3000c01v1Index, agw3000c01v1AsiIn2Fail }
		STATUS current
		DESCRIPTION
			"ASI  IN 2 fail status Trap"
		::= { agw3000c01v1Traps 349 }

		-- 1.3.6.1.4.1.10106.2.1.1.404701.3
		agw3000c01v1ExAsiIn2FailTrap NOTIFICATION-TYPE
		OBJECTS { trapCounter, agw3000c01v1Index, agw3000c01v1ExAsiIn2Fail }
		STATUS current
		DESCRIPTION
			"ASI  IN 2 fail external input fail status Trap"
		::= { agw3000c01v1Traps 351 }

		-- 1.3.6.1.4.1.10106.2.1.1.404701.3
		agw3000c01v1IpIn1FailTrap NOTIFICATION-TYPE
		OBJECTS { trapCounter, agw3000c01v1Index, agw3000c01v1IpIn1Fail }
		STATUS current
		DESCRIPTION
			"IP IN 1 fail status Trap"
		::= { agw3000c01v1Traps 353 }

		-- 1.3.6.1.4.1.10106.2.1.1.404701.3
		agw3000c01v1ExIpIn1FailTrap NOTIFICATION-TYPE
		OBJECTS { trapCounter, agw3000c01v1Index, agw3000c01v1ExIpIn1Fail }
		STATUS current
		DESCRIPTION
			"IP IN 1 external input fail status Trap"
		::= { agw3000c01v1Traps 355 }

		-- 1.3.6.1.4.1.10106.2.1.1.404701.3
		agw3000c01v1IpIn2FailTrap NOTIFICATION-TYPE
		OBJECTS { trapCounter, agw3000c01v1Index, agw3000c01v1IpIn2Fail }
		STATUS current
		DESCRIPTION
			"IP IN 2 input status Trap"
		::= { agw3000c01v1Traps 357 }

		-- 1.3.6.1.4.1.10106.2.1.1.404701.3
		agw3000c01v1ExIpIn2FailTrap NOTIFICATION-TYPE
		OBJECTS { trapCounter, agw3000c01v1Index, agw3000c01v1ExIpIn2Fail }
		STATUS current
		DESCRIPTION
			"IP IN 2 external input fail status Trap"
		::= { agw3000c01v1Traps 359 }

		-- 1.3.6.1.4.1.10106.2.1.1.404702
		agw3000c01v2Traps OBJECT IDENTIFIER ::= { albalaTraps 404702 }

		-- 1.3.6.1.4.1.10106.2.1.1.404702.3
		agw3000c01v2ModeTrap NOTIFICATION-TYPE
		OBJECTS { trapCounter, agw3000c01v2Index, agw3000c01v2Mode }
		STATUS current
		DESCRIPTION
			"Allows selecting the switching mode Trap"
		::= { agw3000c01v2Traps 3 }

		-- 1.3.6.1.4.1.10106.2.1.1.404702.3
		agw3000c01v2DvbTModeTrap NOTIFICATION-TYPE
		OBJECTS { trapCounter, agw3000c01v2Index, agw3000c01v2DvbTMode }
		STATUS current
		DESCRIPTION
			"Selects DVB-T mode. Seamless operation is only possible in DVB-T mode Trap"
		::= { agw3000c01v2Traps 5 }

		-- 1.3.6.1.4.1.10106.2.1.1.404702.3
		agw3000c01v2AsiOut1InTrap NOTIFICATION-TYPE
		OBJECTS { trapCounter, agw3000c01v2Index, agw3000c01v2AsiOut1In }
		STATUS current
		DESCRIPTION
			"ASI OUT 2 - Selected input Trap"
		::= { agw3000c01v2Traps 27 }

		-- 1.3.6.1.4.1.10106.2.1.1.404702.3
		agw3000c01v2AsiOut2InTrap NOTIFICATION-TYPE
		OBJECTS { trapCounter, agw3000c01v2Index, agw3000c01v2AsiOut2In }
		STATUS current
		DESCRIPTION
			"ASI OUT 1 - Selected input Trap"
		::= { agw3000c01v2Traps 29 }

		-- 1.3.6.1.4.1.10106.2.1.1.404702.3
		agw3000c01v2IpOut1InTrap NOTIFICATION-TYPE
		OBJECTS { trapCounter, agw3000c01v2Index, agw3000c01v2IpOut1In }
		STATUS current
		DESCRIPTION
			"IP OUT 1 - Selected input Trap"
		::= { agw3000c01v2Traps 31 }

		-- 1.3.6.1.4.1.10106.2.1.1.404702.3
		agw3000c01v2IpOut2InTrap NOTIFICATION-TYPE
		OBJECTS { trapCounter, agw3000c01v2Index, agw3000c01v2IpOut2In }
		STATUS current
		DESCRIPTION
			"IP OUT 2 - Selected input Trap"
		::= { agw3000c01v2Traps 33 }

		-- 1.3.6.1.4.1.10106.2.1.1.404702.3
		agw3000c01v2AsiIn1FailTrap NOTIFICATION-TYPE
		OBJECTS { trapCounter, agw3000c01v2Index, agw3000c01v2AsiIn1Fail }
		STATUS current
		DESCRIPTION
			"ASI IN 1 fail status Trap"
		::= { agw3000c01v2Traps 347 }

		-- 1.3.6.1.4.1.10106.2.1.1.404702.3
		agw3000c01v2ExAsiIn1FailTrap NOTIFICATION-TYPE
		OBJECTS { trapCounter, agw3000c01v2Index, agw3000c01v2ExAsiIn1Fail }
		STATUS current
		DESCRIPTION
			"ASI IN 1 external input fail status Trap"
		::= { agw3000c01v2Traps 349 }

		-- 1.3.6.1.4.1.10106.2.1.1.404702.3
		agw3000c01v2AsiIn2FailTrap NOTIFICATION-TYPE
		OBJECTS { trapCounter, agw3000c01v2Index, agw3000c01v2AsiIn2Fail }
		STATUS current
		DESCRIPTION
			"ASI  IN 2 fail status Trap"
		::= { agw3000c01v2Traps 351 }

		-- 1.3.6.1.4.1.10106.2.1.1.404702.3
		agw3000c01v2ExAsiIn2FailTrap NOTIFICATION-TYPE
		OBJECTS { trapCounter, agw3000c01v2Index, agw3000c01v2ExAsiIn2Fail }
		STATUS current
		DESCRIPTION
			"ASI  IN 2 fail external input fail status Trap"
		::= { agw3000c01v2Traps 353 }

		-- 1.3.6.1.4.1.10106.2.1.1.404702.3
		agw3000c01v2IpIn1FailTrap NOTIFICATION-TYPE
		OBJECTS { trapCounter, agw3000c01v2Index, agw3000c01v2IpIn1Fail }
		STATUS current
		DESCRIPTION
			"IP IN 1 fail status Trap"
		::= { agw3000c01v2Traps 355 }

		-- 1.3.6.1.4.1.10106.2.1.1.404702.3
		agw3000c01v2ExIpIn1FailTrap NOTIFICATION-TYPE
		OBJECTS { trapCounter, agw3000c01v2Index, agw3000c01v2ExIpIn1Fail }
		STATUS current
		DESCRIPTION
			"IP IN 1 external input fail status Trap"
		::= { agw3000c01v2Traps 357 }

		-- 1.3.6.1.4.1.10106.2.1.1.404702.3
		agw3000c01v2IpIn2FailTrap NOTIFICATION-TYPE
		OBJECTS { trapCounter, agw3000c01v2Index, agw3000c01v2IpIn2Fail }
		STATUS current
		DESCRIPTION
			"IP IN 2 input status Trap"
		::= { agw3000c01v2Traps 359 }

		-- 1.3.6.1.4.1.10106.2.1.1.404702.3
		agw3000c01v2ExIpIn2FailTrap NOTIFICATION-TYPE
		OBJECTS { trapCounter, agw3000c01v2Index, agw3000c01v2ExIpIn2Fail }
		STATUS current
		DESCRIPTION
			"IP IN 2 external input fail status Trap"
		::= { agw3000c01v2Traps 361 }

		-- 1.3.6.1.4.1.10106.2.1.1.407601
		ham3000c02v1Traps OBJECT IDENTIFIER ::= { albalaTraps 407601 }

		-- 1.3.6.1.4.1.10106.2.1.1.407601.3
		ham3000c02v1NoSignalMainTrap NOTIFICATION-TYPE
		OBJECTS { trapCounter, ham3000c02v1Index, ham3000c02v1NoSignalMain }
		STATUS current
		DESCRIPTION
			"There is no SDI signal or the format is not supported in PGM IN Trap"
		::= { ham3000c02v1Traps 305 }

		-- 1.3.6.1.4.1.10106.2.1.1.407601.3
		ham3000c02v1UnlockMainTrap NOTIFICATION-TYPE
		OBJECTS { trapCounter, ham3000c02v1Index, ham3000c02v1UnlockMain }
		STATUS current
		DESCRIPTION
			"Indicates signal unlock fail Trap"
		::= { ham3000c02v1Traps 307 }

		-- 1.3.6.1.4.1.10106.2.1.1.407601.3
		ham3000c02v1EdhErrorMainTrap NOTIFICATION-TYPE
		OBJECTS { trapCounter, ham3000c02v1Index, ham3000c02v1EdhErrorMain }
		STATUS current
		DESCRIPTION
			"There are EDH/CRC errors on PGM IN Trap"
		::= { ham3000c02v1Traps 309 }

		-- 1.3.6.1.4.1.10106.2.1.1.407601.3
		ham3000c02v1RefAbsentTrap NOTIFICATION-TYPE
		OBJECTS { trapCounter, ham3000c02v1Index, ham3000c02v1RefAbsent }
		STATUS current
		DESCRIPTION
			"There is no reference signal Trap"
		::= { ham3000c02v1Traps 317 }

		-- 1.3.6.1.4.1.10106.2.1.1.407601.3
		ham3000c02v1RefUnlockTrap NOTIFICATION-TYPE
		OBJECTS { trapCounter, ham3000c02v1Index, ham3000c02v1RefUnlock }
		STATUS current
		DESCRIPTION
			"Reference input unlock fail Trap"
		::= { ham3000c02v1Traps 319 }

		-- 1.3.6.1.4.1.10106.2.1.1.407601.3
		ham3000c02v1Gr1MainPresTrap NOTIFICATION-TYPE
		OBJECTS { trapCounter, ham3000c02v1Index, ham3000c02v1Gr1MainPres }
		STATUS current
		DESCRIPTION
			"Indicates group 1 presence in PGM IN Trap"
		::= { ham3000c02v1Traps 331 }

		-- 1.3.6.1.4.1.10106.2.1.1.407601.3
		ham3000c02v1Gr2MainPresTrap NOTIFICATION-TYPE
		OBJECTS { trapCounter, ham3000c02v1Index, ham3000c02v1Gr2MainPres }
		STATUS current
		DESCRIPTION
			"Indicates group 2 presence in PGM IN Trap"
		::= { ham3000c02v1Traps 333 }

		-- 1.3.6.1.4.1.10106.2.1.1.407601.3
		ham3000c02v1Gr3MainPresTrap NOTIFICATION-TYPE
		OBJECTS { trapCounter, ham3000c02v1Index, ham3000c02v1Gr3MainPres }
		STATUS current
		DESCRIPTION
			"Indicates group 3 presence in PGM IN Trap"
		::= { ham3000c02v1Traps 335 }

		-- 1.3.6.1.4.1.10106.2.1.1.407601.3
		ham3000c02v1Gr4MainPresTrap NOTIFICATION-TYPE
		OBJECTS { trapCounter, ham3000c02v1Index, ham3000c02v1Gr4MainPres }
		STATUS current
		DESCRIPTION
			"Indicates group 4 presence in PGM IN Trap"
		::= { ham3000c02v1Traps 337 }

		-- 1.3.6.1.4.1.10106.2.1.1.407601.3
		ham3000c02v1AudStatMainTrap NOTIFICATION-TYPE
		OBJECTS { trapCounter, ham3000c02v1Index, ham3000c02v1AudStatMain }
		STATUS current
		DESCRIPTION
			"Indicates audio fail in audio channels embedded in PGM IN Trap"
		::= { ham3000c02v1Traps 355 }

		-- 1.3.6.1.4.1.10106.2.1.1.407601.3
		ham3000c02v1AudStatAuxTrap NOTIFICATION-TYPE
		OBJECTS { trapCounter, ham3000c02v1Index, ham3000c02v1AudStatAux }
		STATUS current
		DESCRIPTION
			"Indicates audio fail in audio channels embedded in AUX IN Trap"
		::= { ham3000c02v1Traps 357 }

		-- 1.3.6.1.4.1.10106.2.1.1.407601.3
		ham3000c02v1AudStatAes1Trap NOTIFICATION-TYPE
		OBJECTS { trapCounter, ham3000c02v1Index, ham3000c02v1AudStatAes1 }
		STATUS current
		DESCRIPTION
			"Indicates audio fail in AES1 input Trap"
		::= { ham3000c02v1Traps 359 }

		-- 1.3.6.1.4.1.10106.2.1.1.407601.3
		ham3000c02v1AudStatAes2Trap NOTIFICATION-TYPE
		OBJECTS { trapCounter, ham3000c02v1Index, ham3000c02v1AudStatAes2 }
		STATUS current
		DESCRIPTION
			"Indicates audio fail in AES2 input Trap"
		::= { ham3000c02v1Traps 361 }

		-- 1.3.6.1.4.1.10106.2.1.1.407601.3
		ham3000c02v1AudStatAnlg1Trap NOTIFICATION-TYPE
		OBJECTS { trapCounter, ham3000c02v1Index, ham3000c02v1AudStatAnlg1 }
		STATUS current
		DESCRIPTION
			"Indicates audio fail in analogue 1 inputs Trap"
		::= { ham3000c02v1Traps 363 }

		-- 1.3.6.1.4.1.10106.2.1.1.407601.3
		ham3000c02v1AudStatAnlg2Trap NOTIFICATION-TYPE
		OBJECTS { trapCounter, ham3000c02v1Index, ham3000c02v1AudStatAnlg2 }
		STATUS current
		DESCRIPTION
			"Indicates audio fail in analogue 2 inputs Trap"
		::= { ham3000c02v1Traps 365 }

		-- 1.3.6.1.4.1.10106.2.1.1.407601.3
		ham3000c02v1OvldPgmOutTrap NOTIFICATION-TYPE
		OBJECTS { trapCounter, ham3000c02v1Index, ham3000c02v1OvldPgmOut }
		STATUS current
		DESCRIPTION
			"Indicates audio overload in SDI output PGM OUT Trap"
		::= { ham3000c02v1Traps 367 }

		-- 1.3.6.1.4.1.10106.2.1.1.407601.3
		ham3000c02v1OvldAes1OutTrap NOTIFICATION-TYPE
		OBJECTS { trapCounter, ham3000c02v1Index, ham3000c02v1OvldAes1Out }
		STATUS current
		DESCRIPTION
			"Indicates audio overload in AES1 OUT Trap"
		::= { ham3000c02v1Traps 369 }

		-- 1.3.6.1.4.1.10106.2.1.1.407601.3
		ham3000c02v1OvldAes2OutTrap NOTIFICATION-TYPE
		OBJECTS { trapCounter, ham3000c02v1Index, ham3000c02v1OvldAes2Out }
		STATUS current
		DESCRIPTION
			"Indicates audio overload in AES2 OUT Trap"
		::= { ham3000c02v1Traps 371 }

		-- 1.3.6.1.4.1.10106.2.1.1.407601.3
		ham3000c02v1SilPgmOutTrap NOTIFICATION-TYPE
		OBJECTS { trapCounter, ham3000c02v1Index, ham3000c02v1SilPgmOut }
		STATUS current
		DESCRIPTION
			"Indicates audio silence in SDI_PGM_OUT Trap"
		::= { ham3000c02v1Traps 373 }

		-- 1.3.6.1.4.1.10106.2.1.1.407601.3
		ham3000c02v1SilAes1OutTrap NOTIFICATION-TYPE
		OBJECTS { trapCounter, ham3000c02v1Index, ham3000c02v1SilAes1Out }
		STATUS current
		DESCRIPTION
			"Indicates audio silence in AES1_OUT Trap"
		::= { ham3000c02v1Traps 375 }

		-- 1.3.6.1.4.1.10106.2.1.1.407601.3
		ham3000c02v1SilAes2OutTrap NOTIFICATION-TYPE
		OBJECTS { trapCounter, ham3000c02v1Index, ham3000c02v1SilAes2Out }
		STATUS current
		DESCRIPTION
			"Indicates audio silence in AES2_OUT Trap"
		::= { ham3000c02v1Traps 377 }

		-- 1.3.6.1.4.1.10106.2.1.1.407701
		ham3000c03v1Traps OBJECT IDENTIFIER ::= { albalaTraps 407701 }

		-- 1.3.6.1.4.1.10106.2.1.1.407701.3
		ham3000c03v1NoSignalMainTrap NOTIFICATION-TYPE
		OBJECTS { trapCounter, ham3000c03v1Index, ham3000c03v1NoSignalMain }
		STATUS current
		DESCRIPTION
			"There is no SDI signal or the format is not supported in PGM IN Trap"
		::= { ham3000c03v1Traps 353 }

		-- 1.3.6.1.4.1.10106.2.1.1.407701.3
		ham3000c03v1UnlockMainTrap NOTIFICATION-TYPE
		OBJECTS { trapCounter, ham3000c03v1Index, ham3000c03v1UnlockMain }
		STATUS current
		DESCRIPTION
			"Indicates signal unlock fail Trap"
		::= { ham3000c03v1Traps 355 }

		-- 1.3.6.1.4.1.10106.2.1.1.407701.3
		ham3000c03v1EdhErrorMainTrap NOTIFICATION-TYPE
		OBJECTS { trapCounter, ham3000c03v1Index, ham3000c03v1EdhErrorMain }
		STATUS current
		DESCRIPTION
			"There are EDH/CRC errors on PGM IN Trap"
		::= { ham3000c03v1Traps 357 }

		-- 1.3.6.1.4.1.10106.2.1.1.407701.3
		ham3000c03v1RefAbsentTrap NOTIFICATION-TYPE
		OBJECTS { trapCounter, ham3000c03v1Index, ham3000c03v1RefAbsent }
		STATUS current
		DESCRIPTION
			"There is no reference signal Trap"
		::= { ham3000c03v1Traps 365 }

		-- 1.3.6.1.4.1.10106.2.1.1.407701.3
		ham3000c03v1RefUnlockTrap NOTIFICATION-TYPE
		OBJECTS { trapCounter, ham3000c03v1Index, ham3000c03v1RefUnlock }
		STATUS current
		DESCRIPTION
			"Reference input unlock fail Trap"
		::= { ham3000c03v1Traps 367 }

		-- 1.3.6.1.4.1.10106.2.1.1.407701.3
		ham3000c03v1Gr1MainPresTrap NOTIFICATION-TYPE
		OBJECTS { trapCounter, ham3000c03v1Index, ham3000c03v1Gr1MainPres }
		STATUS current
		DESCRIPTION
			"Indicates group 1 presence in PGM IN Trap"
		::= { ham3000c03v1Traps 379 }

		-- 1.3.6.1.4.1.10106.2.1.1.407701.3
		ham3000c03v1Gr2MainPresTrap NOTIFICATION-TYPE
		OBJECTS { trapCounter, ham3000c03v1Index, ham3000c03v1Gr2MainPres }
		STATUS current
		DESCRIPTION
			"Indicates group 2 presence in PGM IN Trap"
		::= { ham3000c03v1Traps 381 }

		-- 1.3.6.1.4.1.10106.2.1.1.407701.3
		ham3000c03v1Gr3MainPresTrap NOTIFICATION-TYPE
		OBJECTS { trapCounter, ham3000c03v1Index, ham3000c03v1Gr3MainPres }
		STATUS current
		DESCRIPTION
			"Indicates group 3 presence in PGM IN Trap"
		::= { ham3000c03v1Traps 383 }

		-- 1.3.6.1.4.1.10106.2.1.1.407701.3
		ham3000c03v1Gr4MainPresTrap NOTIFICATION-TYPE
		OBJECTS { trapCounter, ham3000c03v1Index, ham3000c03v1Gr4MainPres }
		STATUS current
		DESCRIPTION
			"Indicates group 4 presence in PGM IN Trap"
		::= { ham3000c03v1Traps 385 }

		-- 1.3.6.1.4.1.10106.2.1.1.407701.3
		ham3000c03v1AudStatMainTrap NOTIFICATION-TYPE
		OBJECTS { trapCounter, ham3000c03v1Index, ham3000c03v1AudStatMain }
		STATUS current
		DESCRIPTION
			"Indicates audio fail in audio channels embedded in PGM IN Trap"
		::= { ham3000c03v1Traps 403 }

		-- 1.3.6.1.4.1.10106.2.1.1.407701.3
		ham3000c03v1AudStatAuxTrap NOTIFICATION-TYPE
		OBJECTS { trapCounter, ham3000c03v1Index, ham3000c03v1AudStatAux }
		STATUS current
		DESCRIPTION
			"Indicates audio fail in audio channels embedded in AUX IN Trap"
		::= { ham3000c03v1Traps 405 }

		-- 1.3.6.1.4.1.10106.2.1.1.407701.3
		ham3000c03v1AudStatAes1Trap NOTIFICATION-TYPE
		OBJECTS { trapCounter, ham3000c03v1Index, ham3000c03v1AudStatAes1 }
		STATUS current
		DESCRIPTION
			"Indicates audio fail in AES1 input Trap"
		::= { ham3000c03v1Traps 407 }

		-- 1.3.6.1.4.1.10106.2.1.1.407701.3
		ham3000c03v1AudStatAes2Trap NOTIFICATION-TYPE
		OBJECTS { trapCounter, ham3000c03v1Index, ham3000c03v1AudStatAes2 }
		STATUS current
		DESCRIPTION
			"Indicates audio fail in AES2 input Trap"
		::= { ham3000c03v1Traps 409 }

		-- 1.3.6.1.4.1.10106.2.1.1.407701.3
		ham3000c03v1OvldPgmOutTrap NOTIFICATION-TYPE
		OBJECTS { trapCounter, ham3000c03v1Index, ham3000c03v1OvldPgmOut }
		STATUS current
		DESCRIPTION
			"Indicates audio overload in SDI output PGM OUT Trap"
		::= { ham3000c03v1Traps 411 }

		-- 1.3.6.1.4.1.10106.2.1.1.407701.3
		ham3000c03v1OvldAes1OutTrap NOTIFICATION-TYPE
		OBJECTS { trapCounter, ham3000c03v1Index, ham3000c03v1OvldAes1Out }
		STATUS current
		DESCRIPTION
			"Indicates audio overload in AES1 OUT Trap"
		::= { ham3000c03v1Traps 413 }

		-- 1.3.6.1.4.1.10106.2.1.1.407701.3
		ham3000c03v1OvldAes2OutTrap NOTIFICATION-TYPE
		OBJECTS { trapCounter, ham3000c03v1Index, ham3000c03v1OvldAes2Out }
		STATUS current
		DESCRIPTION
			"Indicates audio overload in AES2 OUT Trap"
		::= { ham3000c03v1Traps 415 }

		-- 1.3.6.1.4.1.10106.2.1.1.407701.3
		ham3000c03v1OvldAnlg1OutTrap NOTIFICATION-TYPE
		OBJECTS { trapCounter, ham3000c03v1Index, ham3000c03v1OvldAnlg1Out }
		STATUS current
		DESCRIPTION
			"Indicates audio overload in ANALOG1 OUT Trap"
		::= { ham3000c03v1Traps 417 }

		-- 1.3.6.1.4.1.10106.2.1.1.407701.3
		ham3000c03v1OvldAnlg2OutTrap NOTIFICATION-TYPE
		OBJECTS { trapCounter, ham3000c03v1Index, ham3000c03v1OvldAnlg2Out }
		STATUS current
		DESCRIPTION
			"Indicates audio overload in ANALOG2 OUT Trap"
		::= { ham3000c03v1Traps 419 }

		-- 1.3.6.1.4.1.10106.2.1.1.407701.3
		ham3000c03v1SilPgmOutTrap NOTIFICATION-TYPE
		OBJECTS { trapCounter, ham3000c03v1Index, ham3000c03v1SilPgmOut }
		STATUS current
		DESCRIPTION
			"Indicates audio silence in SDI_PGM_OUT Trap"
		::= { ham3000c03v1Traps 421 }

		-- 1.3.6.1.4.1.10106.2.1.1.407701.3
		ham3000c03v1SilAes1OutTrap NOTIFICATION-TYPE
		OBJECTS { trapCounter, ham3000c03v1Index, ham3000c03v1SilAes1Out }
		STATUS current
		DESCRIPTION
			"Indicates audio silence in AES1_OUT Trap"
		::= { ham3000c03v1Traps 423 }

		-- 1.3.6.1.4.1.10106.2.1.1.407701.3
		ham3000c03v1SilAes2OutTrap NOTIFICATION-TYPE
		OBJECTS { trapCounter, ham3000c03v1Index, ham3000c03v1SilAes2Out }
		STATUS current
		DESCRIPTION
			"Indicates audio silence in AES2_OUT Trap"
		::= { ham3000c03v1Traps 425 }

		-- 1.3.6.1.4.1.10106.2.1.1.407701.3
		ham3000c03v1SilAnlg1OutTrap NOTIFICATION-TYPE
		OBJECTS { trapCounter, ham3000c03v1Index, ham3000c03v1SilAnlg1Out }
		STATUS current
		DESCRIPTION
			"Indicates audio silence in ANALOG1_OUT Trap"
		::= { ham3000c03v1Traps 427 }

		-- 1.3.6.1.4.1.10106.2.1.1.407701.3
		ham3000c03v1SilAnlg2OutTrap NOTIFICATION-TYPE
		OBJECTS { trapCounter, ham3000c03v1Index, ham3000c03v1SilAnlg2Out }
		STATUS current
		DESCRIPTION
			"Indicates audio silence in ANALOG2_OUT Trap"
		::= { ham3000c03v1Traps 429 }

		-- 1.3.6.1.4.1.10106.2.1.1.412201
		hop3147c02v1Traps OBJECT IDENTIFIER ::= { albalaTraps 412201 }

		-- 1.3.6.1.4.1.10106.2.1.1.412201.3
		hop3147c02v1TxtFailTrap NOTIFICATION-TYPE
		OBJECTS { trapCounter, hop3147c02v1Index, hop3147c02v1TxtFail }
		STATUS current
		DESCRIPTION
			"Teletext signal not found Trap"
		::= { hop3147c02v1Traps 271 }

		-- 1.3.6.1.4.1.10106.2.1.1.412201.3
		hop3147c02v1TxtInsFailTrap NOTIFICATION-TYPE
		OBJECTS { trapCounter, hop3147c02v1Index, hop3147c02v1TxtInsFail }
		STATUS current
		DESCRIPTION
			"OP47 packet can not be inserted Trap"
		::= { hop3147c02v1Traps 273 }

		-- 1.3.6.1.4.1.10106.2.1.1.412201.3
		hop3147c02v1AudioFailTrap NOTIFICATION-TYPE
		OBJECTS { trapCounter, hop3147c02v1Index, hop3147c02v1AudioFail }
		STATUS current
		DESCRIPTION
			"Audio presence fail Trap"
		::= { hop3147c02v1Traps 275 }

		-- 1.3.6.1.4.1.10106.2.1.1.412201.3
		hop3147c02v1AudioInsFailTrap NOTIFICATION-TYPE
		OBJECTS { trapCounter, hop3147c02v1Index, hop3147c02v1AudioInsFail }
		STATUS current
		DESCRIPTION
			"Audio insertion fail Trap"
		::= { hop3147c02v1Traps 277 }

		-- 1.3.6.1.4.1.10106.2.1.1.412201.3
		hop3147c02v1ViiInsFailTrap NOTIFICATION-TYPE
		OBJECTS { trapCounter, hop3147c02v1Index, hop3147c02v1ViiInsFail }
		STATUS current
		DESCRIPTION
			"VII insertion fail Trap"
		::= { hop3147c02v1Traps 279 }

		-- 1.3.6.1.4.1.10106.2.1.1.412201.3
		hop3147c02v1WssInsFailTrap NOTIFICATION-TYPE
		OBJECTS { trapCounter, hop3147c02v1Index, hop3147c02v1WssInsFail }
		STATUS current
		DESCRIPTION
			"WSS insertion fail Trap"
		::= { hop3147c02v1Traps 281 }

		-- 1.3.6.1.4.1.10106.2.1.1.412201.3
		hop3147c02v1AfdInsFailTrap NOTIFICATION-TYPE
		OBJECTS { trapCounter, hop3147c02v1Index, hop3147c02v1AfdInsFail }
		STATUS current
		DESCRIPTION
			"AFD  (SMPTE 2016-3) insertion fail Trap"
		::= { hop3147c02v1Traps 283 }

		-- 1.3.6.1.4.1.10106.2.1.1.412201.3
		hop3147c02v1NoSignal0Trap NOTIFICATION-TYPE
		OBJECTS { trapCounter, hop3147c02v1Index, hop3147c02v1NoSignal0 }
		STATUS current
		DESCRIPTION
			"There is no SDI signal or the format is not supported MAIN INPUT Trap"
		::= { hop3147c02v1Traps 285 }

		-- 1.3.6.1.4.1.10106.2.1.1.412201.3
		hop3147c02v1Unlocked0Trap NOTIFICATION-TYPE
		OBJECTS { trapCounter, hop3147c02v1Index, hop3147c02v1Unlocked0 }
		STATUS current
		DESCRIPTION
			"Indicates signal unlock fail MAIN INPUT Trap"
		::= { hop3147c02v1Traps 287 }

		-- 1.3.6.1.4.1.10106.2.1.1.412201.3
		hop3147c02v1EdhCrc0Trap NOTIFICATION-TYPE
		OBJECTS { trapCounter, hop3147c02v1Index, hop3147c02v1EdhCrc0 }
		STATUS current
		DESCRIPTION
			"There are EDH/CRC errors on SDI signal MAIN INPUT Trap"
		::= { hop3147c02v1Traps 289 }

		-- 1.3.6.1.4.1.10106.2.1.1.412201.3
		hop3147c02v1NoSignal1Trap NOTIFICATION-TYPE
		OBJECTS { trapCounter, hop3147c02v1Index, hop3147c02v1NoSignal1 }
		STATUS current
		DESCRIPTION
			"There is no SDI signal or the format is not supported AUX INPUT Trap"
		::= { hop3147c02v1Traps 293 }

		-- 1.3.6.1.4.1.10106.2.1.1.412201.3
		hop3147c02v1Unlocked1Trap NOTIFICATION-TYPE
		OBJECTS { trapCounter, hop3147c02v1Index, hop3147c02v1Unlocked1 }
		STATUS current
		DESCRIPTION
			"Indicates signal unlock fail AUX INPUT Trap"
		::= { hop3147c02v1Traps 295 }

		-- 1.3.6.1.4.1.10106.2.1.1.412201.3
		hop3147c02v1EdhCrc1Trap NOTIFICATION-TYPE
		OBJECTS { trapCounter, hop3147c02v1Index, hop3147c02v1EdhCrc1 }
		STATUS current
		DESCRIPTION
			"There are EDH/CRC errors on SDI signal AUX INPUT Trap"
		::= { hop3147c02v1Traps 297 }

		-- 1.3.6.1.4.1.10106.2.1.1.412201.3
		hop3147c02v1Gpi1Trap NOTIFICATION-TYPE
		OBJECTS { trapCounter, hop3147c02v1Index, hop3147c02v1Gpi1 }
		STATUS current
		DESCRIPTION
			"Transmitted GPI1 Trap"
		::= { hop3147c02v1Traps 301 }

		-- 1.3.6.1.4.1.10106.2.1.1.412201.3
		hop3147c02v1Gpi2Trap NOTIFICATION-TYPE
		OBJECTS { trapCounter, hop3147c02v1Index, hop3147c02v1Gpi2 }
		STATUS current
		DESCRIPTION
			"Transmitted GPI2 Trap"
		::= { hop3147c02v1Traps 303 }

		-- 1.3.6.1.4.1.10106.2.1.1.412201.3
		hop3147c02v1Gpi3Trap NOTIFICATION-TYPE
		OBJECTS { trapCounter, hop3147c02v1Index, hop3147c02v1Gpi3 }
		STATUS current
		DESCRIPTION
			"Transmitted GPI3 Trap"
		::= { hop3147c02v1Traps 305 }

		-- 1.3.6.1.4.1.10106.2.1.1.412201.3
		hop3147c02v1Gpi4Trap NOTIFICATION-TYPE
		OBJECTS { trapCounter, hop3147c02v1Index, hop3147c02v1Gpi4 }
		STATUS current
		DESCRIPTION
			"Transmitted GPI4 Trap"
		::= { hop3147c02v1Traps 307 }

		-- 1.3.6.1.4.1.10106.2.1.1.412201.3
		hop3147c02v1Gpi5Trap NOTIFICATION-TYPE
		OBJECTS { trapCounter, hop3147c02v1Index, hop3147c02v1Gpi5 }
		STATUS current
		DESCRIPTION
			"Transmitted GPI5 Trap"
		::= { hop3147c02v1Traps 309 }

		-- 1.3.6.1.4.1.10106.2.1.1.412201.3
		hop3147c02v1Gpi6Trap NOTIFICATION-TYPE
		OBJECTS { trapCounter, hop3147c02v1Index, hop3147c02v1Gpi6 }
		STATUS current
		DESCRIPTION
			"Transmitted GPI6 Trap"
		::= { hop3147c02v1Traps 311 }

		-- 1.3.6.1.4.1.10106.2.1.1.412201.3
		hop3147c02v1Gpi7Trap NOTIFICATION-TYPE
		OBJECTS { trapCounter, hop3147c02v1Index, hop3147c02v1Gpi7 }
		STATUS current
		DESCRIPTION
			"Transmitted GPI7 Trap"
		::= { hop3147c02v1Traps 313 }

		-- 1.3.6.1.4.1.10106.2.1.1.412201.3
		hop3147c02v1Gpi8Trap NOTIFICATION-TYPE
		OBJECTS { trapCounter, hop3147c02v1Index, hop3147c02v1Gpi8 }
		STATUS current
		DESCRIPTION
			"Transmitted GPI8 Trap"
		::= { hop3147c02v1Traps 315 }

		-- 1.3.6.1.4.1.10106.2.1.1.412201.3
		hop3147c02v1Gpo1Trap NOTIFICATION-TYPE
		OBJECTS { trapCounter, hop3147c02v1Index, hop3147c02v1Gpo1 }
		STATUS current
		DESCRIPTION
			"Received GPO1 Trap"
		::= { hop3147c02v1Traps 317 }

		-- 1.3.6.1.4.1.10106.2.1.1.412201.3
		hop3147c02v1Gpo2Trap NOTIFICATION-TYPE
		OBJECTS { trapCounter, hop3147c02v1Index, hop3147c02v1Gpo2 }
		STATUS current
		DESCRIPTION
			"Received GPO2 Trap"
		::= { hop3147c02v1Traps 319 }

		-- 1.3.6.1.4.1.10106.2.1.1.412201.3
		hop3147c02v1Gpo3Trap NOTIFICATION-TYPE
		OBJECTS { trapCounter, hop3147c02v1Index, hop3147c02v1Gpo3 }
		STATUS current
		DESCRIPTION
			"Received GPO3 Trap"
		::= { hop3147c02v1Traps 321 }

		-- 1.3.6.1.4.1.10106.2.1.1.412201.3
		hop3147c02v1Gpo4Trap NOTIFICATION-TYPE
		OBJECTS { trapCounter, hop3147c02v1Index, hop3147c02v1Gpo4 }
		STATUS current
		DESCRIPTION
			"Received GPO4 Trap"
		::= { hop3147c02v1Traps 323 }

		-- 1.3.6.1.4.1.10106.2.1.1.412201.3
		hop3147c02v1Gpo5Trap NOTIFICATION-TYPE
		OBJECTS { trapCounter, hop3147c02v1Index, hop3147c02v1Gpo5 }
		STATUS current
		DESCRIPTION
			"Received GPO5 Trap"
		::= { hop3147c02v1Traps 325 }

		-- 1.3.6.1.4.1.10106.2.1.1.412201.3
		hop3147c02v1Gpo6Trap NOTIFICATION-TYPE
		OBJECTS { trapCounter, hop3147c02v1Index, hop3147c02v1Gpo6 }
		STATUS current
		DESCRIPTION
			"Received GPO6 Trap"
		::= { hop3147c02v1Traps 327 }

		-- 1.3.6.1.4.1.10106.2.1.1.412201.3
		hop3147c02v1Gpo7Trap NOTIFICATION-TYPE
		OBJECTS { trapCounter, hop3147c02v1Index, hop3147c02v1Gpo7 }
		STATUS current
		DESCRIPTION
			"Received GPO7 Trap"
		::= { hop3147c02v1Traps 329 }

		-- 1.3.6.1.4.1.10106.2.1.1.412201.3
		hop3147c02v1Gpo8Trap NOTIFICATION-TYPE
		OBJECTS { trapCounter, hop3147c02v1Index, hop3147c02v1Gpo8 }
		STATUS current
		DESCRIPTION
			"Received GPO8 Trap"
		::= { hop3147c02v1Traps 331 }

		-- 1.3.6.1.4.1.10106.2.1.1.412201.3
		hop3147c02v1VitcAtcPresTrap NOTIFICATION-TYPE
		OBJECTS { trapCounter, hop3147c02v1Index, hop3147c02v1VitcAtcPres }
		STATUS current
		DESCRIPTION
			"VITC-ATC presence in AUX input Trap"
		::= { hop3147c02v1Traps 333 }

		-- 1.3.6.1.4.1.10106.2.1.1.412201.3
		hop3147c02v1TxtAuxPresTrap NOTIFICATION-TYPE
		OBJECTS { trapCounter, hop3147c02v1Index, hop3147c02v1TxtAuxPres }
		STATUS current
		DESCRIPTION
			"TXT presence in AUX input Trap"
		::= { hop3147c02v1Traps 335 }

		-- 1.3.6.1.4.1.10106.2.1.1.412201.3
		hop3147c02v1TxtPresTrap NOTIFICATION-TYPE
		OBJECTS { trapCounter, hop3147c02v1Index, hop3147c02v1TxtPres }
		STATUS current
		DESCRIPTION
			"Teletext presence Trap"
		::= { hop3147c02v1Traps 337 }

		-- 1.3.6.1.4.1.10106.2.1.1.415501
		act3000c01v1Traps OBJECT IDENTIFIER ::= { albalaTraps 415501 }

		-- 1.3.6.1.4.1.10106.2.1.1.415501.3
		act3000c01v1StateSelTrap NOTIFICATION-TYPE
		OBJECTS { trapCounter, act3000c01v1Index, act3000c01v1StateSel }
		STATUS current
		DESCRIPTION
			"Shows the module's current state Trap"
		::= { act3000c01v1Traps 9 }

		-- 1.3.6.1.4.1.10106.2.1.1.415501.3
		act3000c01v1SwitchModeTrap NOTIFICATION-TYPE
		OBJECTS { trapCounter, act3000c01v1Index, act3000c01v1SwitchMode }
		STATUS current
		DESCRIPTION
			"Allows selecting the switching mode Trap"
		::= { act3000c01v1Traps 23 }

		-- 1.3.6.1.4.1.10106.2.1.1.415501.3
		act3000c01v1StatusIn1Trap NOTIFICATION-TYPE
		OBJECTS { trapCounter, act3000c01v1Index, act3000c01v1StatusIn1 }
		STATUS current
		DESCRIPTION
			"Input 1 fail Trap"
		::= { act3000c01v1Traps 105 }

		-- 1.3.6.1.4.1.10106.2.1.1.415501.3
		act3000c01v1StatusIn2Trap NOTIFICATION-TYPE
		OBJECTS { trapCounter, act3000c01v1Index, act3000c01v1StatusIn2 }
		STATUS current
		DESCRIPTION
			"Input 2 fail Trap"
		::= { act3000c01v1Traps 107 }

		-- 1.3.6.1.4.1.10106.2.1.1.415501.3
		act3000c01v1StatusIn1ExtTrap NOTIFICATION-TYPE
		OBJECTS { trapCounter, act3000c01v1Index, act3000c01v1StatusIn1Ext }
		STATUS current
		DESCRIPTION
			"Input 1 external fail Trap"
		::= { act3000c01v1Traps 109 }

		-- 1.3.6.1.4.1.10106.2.1.1.415501.3
		act3000c01v1StatusIn2ExtTrap NOTIFICATION-TYPE
		OBJECTS { trapCounter, act3000c01v1Index, act3000c01v1StatusIn2Ext }
		STATUS current
		DESCRIPTION
			"Input 2 external fail Trap"
		::= { act3000c01v1Traps 111 }

		-- 1.3.6.1.4.1.10106.2.1.1.415501.3
		act3000c01v1StatusIn1ClipTrap NOTIFICATION-TYPE
		OBJECTS { trapCounter, act3000c01v1Index, act3000c01v1StatusIn1Clip }
		STATUS current
		DESCRIPTION
			"Input 1 clipping fail Trap"
		::= { act3000c01v1Traps 113 }

		-- 1.3.6.1.4.1.10106.2.1.1.415501.3
		act3000c01v1StatusIn2ClipTrap NOTIFICATION-TYPE
		OBJECTS { trapCounter, act3000c01v1Index, act3000c01v1StatusIn2Clip }
		STATUS current
		DESCRIPTION
			"Input 2 clipping fail Trap"
		::= { act3000c01v1Traps 115 }

		-- 1.3.6.1.4.1.10106.2.1.1.415501.3
		act3000c01v1SelOut1Trap NOTIFICATION-TYPE
		OBJECTS { trapCounter, act3000c01v1Index, act3000c01v1SelOut1 }
		STATUS current
		DESCRIPTION
			"Output 1 Trap"
		::= { act3000c01v1Traps 117 }

		-- 1.3.6.1.4.1.10106.2.1.1.415501.3
		act3000c01v1SelOut2Trap NOTIFICATION-TYPE
		OBJECTS { trapCounter, act3000c01v1Index, act3000c01v1SelOut2 }
		STATUS current
		DESCRIPTION
			"Output 2 Trap"
		::= { act3000c01v1Traps 119 }

		-- 1.3.6.1.4.1.10106.2.1.1.415501.3
		act3000c01v1Gpi1StatTrap NOTIFICATION-TYPE
		OBJECTS { trapCounter, act3000c01v1Index, act3000c01v1Gpi1Stat }
		STATUS current
		DESCRIPTION
			"GPI1 status (used in remote control) Trap"
		::= { act3000c01v1Traps 125 }

		-- 1.3.6.1.4.1.10106.2.1.1.415501.3
		act3000c01v1FailSil1lTrap NOTIFICATION-TYPE
		OBJECTS { trapCounter, act3000c01v1Index, act3000c01v1FailSil1l }
		STATUS current
		DESCRIPTION
			"Silence in input 1L Trap"
		::= { act3000c01v1Traps 127 }

		-- 1.3.6.1.4.1.10106.2.1.1.415501.3
		act3000c01v1FailOvld1lTrap NOTIFICATION-TYPE
		OBJECTS { trapCounter, act3000c01v1Index, act3000c01v1FailOvld1l }
		STATUS current
		DESCRIPTION
			"Overload in input 1L Trap"
		::= { act3000c01v1Traps 129 }

		-- 1.3.6.1.4.1.10106.2.1.1.415501.3
		act3000c01v1FailClip1lTrap NOTIFICATION-TYPE
		OBJECTS { trapCounter, act3000c01v1Index, act3000c01v1FailClip1l }
		STATUS current
		DESCRIPTION
			"Clipping in input 1L Trap"
		::= { act3000c01v1Traps 131 }

		-- 1.3.6.1.4.1.10106.2.1.1.415501.3
		act3000c01v1FailAnti1Trap NOTIFICATION-TYPE
		OBJECTS { trapCounter, act3000c01v1Index, act3000c01v1FailAnti1 }
		STATUS current
		DESCRIPTION
			"Antiphase fail in input 1 Trap"
		::= { act3000c01v1Traps 133 }

		-- 1.3.6.1.4.1.10106.2.1.1.415501.3
		act3000c01v1FailSil1rTrap NOTIFICATION-TYPE
		OBJECTS { trapCounter, act3000c01v1Index, act3000c01v1FailSil1r }
		STATUS current
		DESCRIPTION
			"Silence in input 1R Trap"
		::= { act3000c01v1Traps 135 }

		-- 1.3.6.1.4.1.10106.2.1.1.415501.3
		act3000c01v1FailOvld1rTrap NOTIFICATION-TYPE
		OBJECTS { trapCounter, act3000c01v1Index, act3000c01v1FailOvld1r }
		STATUS current
		DESCRIPTION
			"Overload in input 1R Trap"
		::= { act3000c01v1Traps 137 }

		-- 1.3.6.1.4.1.10106.2.1.1.415501.3
		act3000c01v1FailClip1rTrap NOTIFICATION-TYPE
		OBJECTS { trapCounter, act3000c01v1Index, act3000c01v1FailClip1r }
		STATUS current
		DESCRIPTION
			"Clipping in input 1R Trap"
		::= { act3000c01v1Traps 139 }

		-- 1.3.6.1.4.1.10106.2.1.1.415501.3
		act3000c01v1FailExt1Trap NOTIFICATION-TYPE
		OBJECTS { trapCounter, act3000c01v1Index, act3000c01v1FailExt1 }
		STATUS current
		DESCRIPTION
			"External fail over input 1 Trap"
		::= { act3000c01v1Traps 141 }

		-- 1.3.6.1.4.1.10106.2.1.1.415501.3
		act3000c01v1FailSil2lTrap NOTIFICATION-TYPE
		OBJECTS { trapCounter, act3000c01v1Index, act3000c01v1FailSil2l }
		STATUS current
		DESCRIPTION
			"Silence in input 2L Trap"
		::= { act3000c01v1Traps 143 }

		-- 1.3.6.1.4.1.10106.2.1.1.415501.3
		act3000c01v1FailOvld2lTrap NOTIFICATION-TYPE
		OBJECTS { trapCounter, act3000c01v1Index, act3000c01v1FailOvld2l }
		STATUS current
		DESCRIPTION
			"Overload in input 2L Trap"
		::= { act3000c01v1Traps 145 }

		-- 1.3.6.1.4.1.10106.2.1.1.415501.3
		act3000c01v1FailClip2lTrap NOTIFICATION-TYPE
		OBJECTS { trapCounter, act3000c01v1Index, act3000c01v1FailClip2l }
		STATUS current
		DESCRIPTION
			"Clipping in input 2L Trap"
		::= { act3000c01v1Traps 147 }

		-- 1.3.6.1.4.1.10106.2.1.1.415501.3
		act3000c01v1FailAnti2Trap NOTIFICATION-TYPE
		OBJECTS { trapCounter, act3000c01v1Index, act3000c01v1FailAnti2 }
		STATUS current
		DESCRIPTION
			"Antiphase fail in input 2 Trap"
		::= { act3000c01v1Traps 149 }

		-- 1.3.6.1.4.1.10106.2.1.1.415501.3
		act3000c01v1FailSil2rTrap NOTIFICATION-TYPE
		OBJECTS { trapCounter, act3000c01v1Index, act3000c01v1FailSil2r }
		STATUS current
		DESCRIPTION
			"Silence in input 2R Trap"
		::= { act3000c01v1Traps 151 }

		-- 1.3.6.1.4.1.10106.2.1.1.415501.3
		act3000c01v1FailOvld2rTrap NOTIFICATION-TYPE
		OBJECTS { trapCounter, act3000c01v1Index, act3000c01v1FailOvld2r }
		STATUS current
		DESCRIPTION
			"Overload in input 2R Trap"
		::= { act3000c01v1Traps 153 }

		-- 1.3.6.1.4.1.10106.2.1.1.415501.3
		act3000c01v1FailClip2rTrap NOTIFICATION-TYPE
		OBJECTS { trapCounter, act3000c01v1Index, act3000c01v1FailClip2r }
		STATUS current
		DESCRIPTION
			"Clipping in input 2R Trap"
		::= { act3000c01v1Traps 155 }

		-- 1.3.6.1.4.1.10106.2.1.1.415501.3
		act3000c01v1FailExt2Trap NOTIFICATION-TYPE
		OBJECTS { trapCounter, act3000c01v1Index, act3000c01v1FailExt2 }
		STATUS current
		DESCRIPTION
			"External fail over input 2 Trap"
		::= { act3000c01v1Traps 157 }

		-- 1.3.6.1.4.1.10106.2.1.1.416301
		hvd2000c01v1Traps OBJECT IDENTIFIER ::= { albalaTraps 416301 }

		-- 1.3.6.1.4.1.10106.2.1.1.416301.3
		hvd2000c01v1NoSigTrap NOTIFICATION-TYPE
		OBJECTS { trapCounter, hvd2000c01v1Index, hvd2000c01v1NoSig }
		STATUS current
		DESCRIPTION
			"Input signal status Trap"
		::= { hvd2000c01v1Traps 3 }

		-- 1.3.6.1.4.1.10106.2.1.1.416301.3
		hvd2000c01v1UnlockTrap NOTIFICATION-TYPE
		OBJECTS { trapCounter, hvd2000c01v1Index, hvd2000c01v1Unlock }
		STATUS current
		DESCRIPTION
			"Indicates signal unlock fail Trap"
		::= { hvd2000c01v1Traps 5 }

		-- 1.3.6.1.4.1.10106.2.1.1.422601
		tsa3000c01v1Traps OBJECT IDENTIFIER ::= { albalaTraps 422601 }

		-- 1.3.6.1.4.1.10106.2.1.1.422601.3
		tsa3000c01v1ModeTrap NOTIFICATION-TYPE
		OBJECTS { trapCounter, tsa3000c01v1Index, tsa3000c01v1Mode }
		STATUS current
		DESCRIPTION
			"Allows selecting the switching mode Trap"
		::= { tsa3000c01v1Traps 3 }

		-- 1.3.6.1.4.1.10106.2.1.1.422601.3
		tsa3000c01v1SelectedInputTrap NOTIFICATION-TYPE
		OBJECTS { trapCounter, tsa3000c01v1Index, tsa3000c01v1SelectedInput }
		STATUS current
		DESCRIPTION
			"Selected input Trap"
		::= { tsa3000c01v1Traps 25 }

		-- 1.3.6.1.4.1.10106.2.1.1.422601.3
		tsa3000c01v1AsiIn1FailTrap NOTIFICATION-TYPE
		OBJECTS { trapCounter, tsa3000c01v1Index, tsa3000c01v1AsiIn1Fail }
		STATUS current
		DESCRIPTION
			"ASI IN 1 fail status Trap"
		::= { tsa3000c01v1Traps 439 }

		-- 1.3.6.1.4.1.10106.2.1.1.422601.3
		tsa3000c01v1ExAsiIn1FailTrap NOTIFICATION-TYPE
		OBJECTS { trapCounter, tsa3000c01v1Index, tsa3000c01v1ExAsiIn1Fail }
		STATUS current
		DESCRIPTION
			"ASI IN 1 external input fail status Trap"
		::= { tsa3000c01v1Traps 441 }

		-- 1.3.6.1.4.1.10106.2.1.1.422601.3
		tsa3000c01v1AsiIn2FailTrap NOTIFICATION-TYPE
		OBJECTS { trapCounter, tsa3000c01v1Index, tsa3000c01v1AsiIn2Fail }
		STATUS current
		DESCRIPTION
			"ASI  IN 2 fail status Trap"
		::= { tsa3000c01v1Traps 443 }

		-- 1.3.6.1.4.1.10106.2.1.1.422601.3
		tsa3000c01v1ExAsiIn2FailTrap NOTIFICATION-TYPE
		OBJECTS { trapCounter, tsa3000c01v1Index, tsa3000c01v1ExAsiIn2Fail }
		STATUS current
		DESCRIPTION
			"ASI  IN 2 fail external input fail status Trap"
		::= { tsa3000c01v1Traps 445 }

		-- 1.3.6.1.4.1.10106.2.1.1.422601.3
		tsa3000c01v1IpIn1FailTrap NOTIFICATION-TYPE
		OBJECTS { trapCounter, tsa3000c01v1Index, tsa3000c01v1IpIn1Fail }
		STATUS current
		DESCRIPTION
			"IP IN 1 fail status Trap"
		::= { tsa3000c01v1Traps 447 }

		-- 1.3.6.1.4.1.10106.2.1.1.422601.3
		tsa3000c01v1ExIpIn1FailTrap NOTIFICATION-TYPE
		OBJECTS { trapCounter, tsa3000c01v1Index, tsa3000c01v1ExIpIn1Fail }
		STATUS current
		DESCRIPTION
			"IP IN 1 external input fail status Trap"
		::= { tsa3000c01v1Traps 449 }

		-- 1.3.6.1.4.1.10106.2.1.1.422601.3
		tsa3000c01v1IpIn2FailTrap NOTIFICATION-TYPE
		OBJECTS { trapCounter, tsa3000c01v1Index, tsa3000c01v1IpIn2Fail }
		STATUS current
		DESCRIPTION
			"IP IN 2 input status Trap"
		::= { tsa3000c01v1Traps 451 }

		-- 1.3.6.1.4.1.10106.2.1.1.422601.3
		tsa3000c01v1ExIpIn2FailTrap NOTIFICATION-TYPE
		OBJECTS { trapCounter, tsa3000c01v1Index, tsa3000c01v1ExIpIn2Fail }
		STATUS current
		DESCRIPTION
			"IP IN 2 external input fail status Trap"
		::= { tsa3000c01v1Traps 453 }

		-- 1.3.6.1.4.1.10106.2.1.1.422601.3
		tsa3000c01v1LinkTrap NOTIFICATION-TYPE
		OBJECTS { trapCounter, tsa3000c01v1Index, tsa3000c01v1Link }
		STATUS current
		DESCRIPTION
			"Ethernet conection status Trap"
		::= { tsa3000c01v1Traps 501 }

		-- 1.3.6.1.4.1.10106.2.1.1.432201
		tle2001c01v1Traps OBJECT IDENTIFIER ::= { albalaTraps 432201 }

		-- 1.3.6.1.4.1.10106.2.1.1.432201.3
		tle2001c01v1Gpi1Trap NOTIFICATION-TYPE
		OBJECTS { trapCounter, tle2001c01v1Index, tle2001c01v1Gpi1 }
		STATUS current
		DESCRIPTION
			"GPI1 status Trap"
		::= { tle2001c01v1Traps 27 }

		-- 1.3.6.1.4.1.10106.2.1.1.432201.3
		tle2001c01v1Gpi2Trap NOTIFICATION-TYPE
		OBJECTS { trapCounter, tle2001c01v1Index, tle2001c01v1Gpi2 }
		STATUS current
		DESCRIPTION
			"GPI2 status Trap"
		::= { tle2001c01v1Traps 29 }

		-- 1.3.6.1.4.1.10106.2.1.1.432201.3
		tle2001c01v1Gpi3Trap NOTIFICATION-TYPE
		OBJECTS { trapCounter, tle2001c01v1Index, tle2001c01v1Gpi3 }
		STATUS current
		DESCRIPTION
			"GPI3 status Trap"
		::= { tle2001c01v1Traps 31 }

		-- 1.3.6.1.4.1.10106.2.1.1.432201.3
		tle2001c01v1Gpi4Trap NOTIFICATION-TYPE
		OBJECTS { trapCounter, tle2001c01v1Index, tle2001c01v1Gpi4 }
		STATUS current
		DESCRIPTION
			"GPI4 status Trap"
		::= { tle2001c01v1Traps 33 }

		-- 1.3.6.1.4.1.10106.2.1.1.432201.3
		tle2001c01v1RedBoardTrap NOTIFICATION-TYPE
		OBJECTS { trapCounter, tle2001c01v1Index, tle2001c01v1RedBoard }
		STATUS current
		DESCRIPTION
			"Indicates that there are two modules in redundant configuration Trap"
		::= { tle2001c01v1Traps 35 }

		-- 1.3.6.1.4.1.10106.2.1.1.432201.3
		tle2001c01v1EthLinkTrap NOTIFICATION-TYPE
		OBJECTS { trapCounter, tle2001c01v1Index, tle2001c01v1EthLink }
		STATUS current
		DESCRIPTION
			"Indicates that the Ethernet link is OK Trap"
		::= { tle2001c01v1Traps 37 }

		-- 1.3.6.1.4.1.10106.2.1.1.432201.3
		tle2001c01v1EthRedActTrap NOTIFICATION-TYPE
		OBJECTS { trapCounter, tle2001c01v1Index, tle2001c01v1EthRedAct }
		STATUS current
		DESCRIPTION
			"Indicates that this is the active module of the redundant configuration Trap"
		::= { tle2001c01v1Traps 39 }

		-- 1.3.6.1.4.1.10106.2.1.1.436601
		psu2000c02v1Traps OBJECT IDENTIFIER ::= { albalaTraps 436601 }

		-- 1.3.6.1.4.1.10106.2.1.1.436601.3
		psu2000c02v1PowerOffTrap NOTIFICATION-TYPE
		OBJECTS { trapCounter, psu2000c02v1Index, psu2000c02v1PowerOff }
		STATUS current
		DESCRIPTION
			"Indicates the power supply status Trap"
		::= { psu2000c02v1Traps 3 }

		-- 1.3.6.1.4.1.10106.2.1.1.436601.3
		psu2000c02v1TempWarningTrap NOTIFICATION-TYPE
		OBJECTS { trapCounter, psu2000c02v1Index, psu2000c02v1TempWarning }
		STATUS current
		DESCRIPTION
			"Indicates that actual temperature is over expected range Trap"
		::= { psu2000c02v1Traps 5 }

		-- 1.3.6.1.4.1.10106.2.1.1.436601.3
		psu2000c02v1TempFailTrap NOTIFICATION-TYPE
		OBJECTS { trapCounter, psu2000c02v1Index, psu2000c02v1TempFail }
		STATUS current
		DESCRIPTION
			"Indicates that actual temperature is over recommended range Trap"
		::= { psu2000c02v1Traps 7 }

		-- 1.3.6.1.4.1.10106.2.1.1.437801
		eop2000c01v1Traps OBJECT IDENTIFIER ::= { albalaTraps 437801 }

		-- 1.3.6.1.4.1.10106.2.1.1.437801.3
		eop2000c01v1InputATrap NOTIFICATION-TYPE
		OBJECTS { trapCounter, eop2000c01v1Index, eop2000c01v1InputA }
		STATUS current
		DESCRIPTION
			"Indicates the input selected Trap"
		::= { eop2000c01v1Traps 3 }

		-- 1.3.6.1.4.1.10106.2.1.1.437801.3
		eop2000c01v1InputBTrap NOTIFICATION-TYPE
		OBJECTS { trapCounter, eop2000c01v1Index, eop2000c01v1InputB }
		STATUS current
		DESCRIPTION
			"Indicates the input selected Trap"
		::= { eop2000c01v1Traps 5 }

		-- 1.3.6.1.4.1.10106.2.1.1.437801.3
		eop2000c01v1UnlockATrap NOTIFICATION-TYPE
		OBJECTS { trapCounter, eop2000c01v1Index, eop2000c01v1UnlockA }
		STATUS current
		DESCRIPTION
			"Indicates signal unlock fail Trap"
		::= { eop2000c01v1Traps 11 }

		-- 1.3.6.1.4.1.10106.2.1.1.437801.3
		eop2000c01v1LFailATrap NOTIFICATION-TYPE
		OBJECTS { trapCounter, eop2000c01v1Index, eop2000c01v1LFailA }
		STATUS current
		DESCRIPTION
			"Indicates a fail in laser Trap"
		::= { eop2000c01v1Traps 13 }

		-- 1.3.6.1.4.1.10106.2.1.1.437801.3
		eop2000c01v1UnlockBTrap NOTIFICATION-TYPE
		OBJECTS { trapCounter, eop2000c01v1Index, eop2000c01v1UnlockB }
		STATUS current
		DESCRIPTION
			"Indicates signal unlock fail Trap"
		::= { eop2000c01v1Traps 21 }

		-- 1.3.6.1.4.1.10106.2.1.1.437801.3
		eop2000c01v1LFailBTrap NOTIFICATION-TYPE
		OBJECTS { trapCounter, eop2000c01v1Index, eop2000c01v1LFailB }
		STATUS current
		DESCRIPTION
			"Indicates a fail in laser Trap"
		::= { eop2000c01v1Traps 23 }

		-- 1.3.6.1.4.1.10106.2.1.1.437801.3
		eop2000c01v1OpTxPresTrap NOTIFICATION-TYPE
		OBJECTS { trapCounter, eop2000c01v1Index, eop2000c01v1OpTxPres }
		STATUS current
		DESCRIPTION
			"Indicates the presence of a SFP TX module Trap"
		::= { eop2000c01v1Traps 31 }

		-- 1.3.6.1.4.1.10106.2.1.1.437801.3
		eop2000c01v1OpRxPresTrap NOTIFICATION-TYPE
		OBJECTS { trapCounter, eop2000c01v1Index, eop2000c01v1OpRxPres }
		STATUS current
		DESCRIPTION
			"Indicates the presence of a SFP RX module Trap"
		::= { eop2000c01v1Traps 33 }

		-- 1.3.6.1.4.1.10106.2.1.1.438701
		avd2001c01v1Traps OBJECT IDENTIFIER ::= { albalaTraps 438701 }

		-- 1.3.6.1.4.1.10106.2.1.1.438701.3
		avd2001c01v1NoSigATrap NOTIFICATION-TYPE
		OBJECTS { trapCounter, avd2001c01v1Index, avd2001c01v1NoSigA }
		STATUS current
		DESCRIPTION
			"Input signal status Trap"
		::= { avd2001c01v1Traps 9 }

		-- 1.3.6.1.4.1.10106.2.1.1.438701.3
		avd2001c01v1UnlockATrap NOTIFICATION-TYPE
		OBJECTS { trapCounter, avd2001c01v1Index, avd2001c01v1UnlockA }
		STATUS current
		DESCRIPTION
			"Indicates signal unlock fail Trap"
		::= { avd2001c01v1Traps 11 }

		-- 1.3.6.1.4.1.10106.2.1.1.438701.3
		avd2001c01v1SyncFormatTrap NOTIFICATION-TYPE
		OBJECTS { trapCounter, avd2001c01v1Index, avd2001c01v1SyncFormat }
		STATUS current
		DESCRIPTION
			"Displays signal's  input format Trap"
		::= { avd2001c01v1Traps 13 }

		-- 1.3.6.1.4.1.10106.2.1.1.442301
		hdc2000c01v1Traps OBJECT IDENTIFIER ::= { albalaTraps 442301 }

		-- 1.3.6.1.4.1.10106.2.1.1.442301.3
		hdc2000c01v1AnaRefFmtTrap NOTIFICATION-TYPE
		OBJECTS { trapCounter, hdc2000c01v1Index, hdc2000c01v1AnaRefFmt }
		STATUS current
		DESCRIPTION
			"Analog reference input format Trap"
		::= { hdc2000c01v1Traps 9 }

		-- 1.3.6.1.4.1.10106.2.1.1.442301.3
		hdc2000c01v1ModeConvTrap NOTIFICATION-TYPE
		OBJECTS { trapCounter, hdc2000c01v1Index, hdc2000c01v1ModeConv }
		STATUS current
		DESCRIPTION
			"Conversion mode Trap"
		::= { hdc2000c01v1Traps 15 }

		-- 1.3.6.1.4.1.10106.2.1.1.442301.3
		hdc2000c01v1OutAfdTrap NOTIFICATION-TYPE
		OBJECTS { trapCounter, hdc2000c01v1Index, hdc2000c01v1OutAfd }
		STATUS current
		DESCRIPTION
			"Output active format description Trap"
		::= { hdc2000c01v1Traps 17 }

		-- 1.3.6.1.4.1.10106.2.1.1.442301.3
		hdc2000c01v1OutCfTrap NOTIFICATION-TYPE
		OBJECTS { trapCounter, hdc2000c01v1Index, hdc2000c01v1OutCf }
		STATUS current
		DESCRIPTION
			"Output coded frame Trap"
		::= { hdc2000c01v1Traps 19 }

		-- 1.3.6.1.4.1.10106.2.1.1.442301.3
		hdc2000c01v1InAfdExpctTrap NOTIFICATION-TYPE
		OBJECTS { trapCounter, hdc2000c01v1Index, hdc2000c01v1InAfdExpct }
		STATUS current
		DESCRIPTION
			"Input expected active format description Trap"
		::= { hdc2000c01v1Traps 21 }

		-- 1.3.6.1.4.1.10106.2.1.1.442301.3
		hdc2000c01v1InCfExpctTrap NOTIFICATION-TYPE
		OBJECTS { trapCounter, hdc2000c01v1Index, hdc2000c01v1InCfExpct }
		STATUS current
		DESCRIPTION
			"Input expected coded frame Trap"
		::= { hdc2000c01v1Traps 23 }

		-- 1.3.6.1.4.1.10106.2.1.1.442301.3
		hdc2000c01v1InAfdDetctTrap NOTIFICATION-TYPE
		OBJECTS { trapCounter, hdc2000c01v1Index, hdc2000c01v1InAfdDetct }
		STATUS current
		DESCRIPTION
			"Input detected AFD Trap"
		::= { hdc2000c01v1Traps 87 }

		-- 1.3.6.1.4.1.10106.2.1.1.442301.3
		hdc2000c01v1InCfDetctTrap NOTIFICATION-TYPE
		OBJECTS { trapCounter, hdc2000c01v1Index, hdc2000c01v1InCfDetct }
		STATUS current
		DESCRIPTION
			"Input detected coded frame Trap"
		::= { hdc2000c01v1Traps 89 }

		-- 1.3.6.1.4.1.10106.2.1.1.442301.3
		hdc2000c01v1InPhyFailTrap NOTIFICATION-TYPE
		OBJECTS { trapCounter, hdc2000c01v1Index, hdc2000c01v1InPhyFail }
		STATUS current
		DESCRIPTION
			"Absence fail Trap"
		::= { hdc2000c01v1Traps 91 }

		-- 1.3.6.1.4.1.10106.2.1.1.442301.3
		hdc2000c01v1InFmtFailTrap NOTIFICATION-TYPE
		OBJECTS { trapCounter, hdc2000c01v1Index, hdc2000c01v1InFmtFail }
		STATUS current
		DESCRIPTION
			"Format fail Trap"
		::= { hdc2000c01v1Traps 93 }

		-- 1.3.6.1.4.1.10106.2.1.1.442301.3
		hdc2000c01v1InIncFailTrap NOTIFICATION-TYPE
		OBJECTS { trapCounter, hdc2000c01v1Index, hdc2000c01v1InIncFail }
		STATUS current
		DESCRIPTION
			"Incompatible format fail Trap"
		::= { hdc2000c01v1Traps 95 }

		-- 1.3.6.1.4.1.10106.2.1.1.442301.3
		hdc2000c01v1InCrcFailTrap NOTIFICATION-TYPE
		OBJECTS { trapCounter, hdc2000c01v1Index, hdc2000c01v1InCrcFail }
		STATUS current
		DESCRIPTION
			"EDH/CRC fail Trap"
		::= { hdc2000c01v1Traps 99 }

		-- 1.3.6.1.4.1.10106.2.1.1.442301.3
		hdc2000c01v1PresAudG1FailTrap NOTIFICATION-TYPE
		OBJECTS { trapCounter, hdc2000c01v1Index, hdc2000c01v1PresAudG1Fail }
		STATUS current
		DESCRIPTION
			"Audio group 1 presence fail Trap"
		::= { hdc2000c01v1Traps 109 }

		-- 1.3.6.1.4.1.10106.2.1.1.442301.3
		hdc2000c01v1PresAudG2FailTrap NOTIFICATION-TYPE
		OBJECTS { trapCounter, hdc2000c01v1Index, hdc2000c01v1PresAudG2Fail }
		STATUS current
		DESCRIPTION
			"Audio group 2 presence fail Trap"
		::= { hdc2000c01v1Traps 111 }

		-- 1.3.6.1.4.1.10106.2.1.1.442301.3
		hdc2000c01v1PresAudG3FailTrap NOTIFICATION-TYPE
		OBJECTS { trapCounter, hdc2000c01v1Index, hdc2000c01v1PresAudG3Fail }
		STATUS current
		DESCRIPTION
			"Audio group 3 presence fail Trap"
		::= { hdc2000c01v1Traps 113 }

		-- 1.3.6.1.4.1.10106.2.1.1.442301.3
		hdc2000c01v1PresAudG4FailTrap NOTIFICATION-TYPE
		OBJECTS { trapCounter, hdc2000c01v1Index, hdc2000c01v1PresAudG4Fail }
		STATUS current
		DESCRIPTION
			"Audio group 4 presence fail Trap"
		::= { hdc2000c01v1Traps 115 }

		-- 1.3.6.1.4.1.10106.2.1.1.442301.3
		hdc2000c01v1RefFailTrap NOTIFICATION-TYPE
		OBJECTS { trapCounter, hdc2000c01v1Index, hdc2000c01v1RefFail }
		STATUS current
		DESCRIPTION
			"Analog reference absence fail Trap"
		::= { hdc2000c01v1Traps 117 }

		-- 1.3.6.1.4.1.10106.2.1.1.442301.3
		hdc2000c01v1RefFmtFailTrap NOTIFICATION-TYPE
		OBJECTS { trapCounter, hdc2000c01v1Index, hdc2000c01v1RefFmtFail }
		STATUS current
		DESCRIPTION
			"Analog reference format fail Trap"
		::= { hdc2000c01v1Traps 119 }

		-- 1.3.6.1.4.1.10106.2.1.1.442301.3
		hdc2000c01v1LockFailTrap NOTIFICATION-TYPE
		OBJECTS { trapCounter, hdc2000c01v1Index, hdc2000c01v1LockFail }
		STATUS current
		DESCRIPTION
			"Reference unlock fail Trap"
		::= { hdc2000c01v1Traps 121 }

		-- 1.3.6.1.4.1.10106.2.1.1.442301.3
		hdc2000c01v1AudPair0FailTrap NOTIFICATION-TYPE
		OBJECTS { trapCounter, hdc2000c01v1Index, hdc2000c01v1AudPair0Fail }
		STATUS current
		DESCRIPTION
			"Audio pair 0 fail Trap"
		::= { hdc2000c01v1Traps 123 }

		-- 1.3.6.1.4.1.10106.2.1.1.442301.3
		hdc2000c01v1AudPair1FailTrap NOTIFICATION-TYPE
		OBJECTS { trapCounter, hdc2000c01v1Index, hdc2000c01v1AudPair1Fail }
		STATUS current
		DESCRIPTION
			"Audio pair 1 fail Trap"
		::= { hdc2000c01v1Traps 125 }

		-- 1.3.6.1.4.1.10106.2.1.1.442301.3
		hdc2000c01v1AudPair2FailTrap NOTIFICATION-TYPE
		OBJECTS { trapCounter, hdc2000c01v1Index, hdc2000c01v1AudPair2Fail }
		STATUS current
		DESCRIPTION
			"Audio pair 2 fail Trap"
		::= { hdc2000c01v1Traps 127 }

		-- 1.3.6.1.4.1.10106.2.1.1.442301.3
		hdc2000c01v1AudPair3FailTrap NOTIFICATION-TYPE
		OBJECTS { trapCounter, hdc2000c01v1Index, hdc2000c01v1AudPair3Fail }
		STATUS current
		DESCRIPTION
			"Audio pair 3 fail Trap"
		::= { hdc2000c01v1Traps 129 }

		-- 1.3.6.1.4.1.10106.2.1.1.442301.3
		hdc2000c01v1AudPair4FailTrap NOTIFICATION-TYPE
		OBJECTS { trapCounter, hdc2000c01v1Index, hdc2000c01v1AudPair4Fail }
		STATUS current
		DESCRIPTION
			"Audio pair 4 fail Trap"
		::= { hdc2000c01v1Traps 131 }

		-- 1.3.6.1.4.1.10106.2.1.1.442301.3
		hdc2000c01v1AudPair5FailTrap NOTIFICATION-TYPE
		OBJECTS { trapCounter, hdc2000c01v1Index, hdc2000c01v1AudPair5Fail }
		STATUS current
		DESCRIPTION
			"Audio pair 5 fail Trap"
		::= { hdc2000c01v1Traps 133 }

		-- 1.3.6.1.4.1.10106.2.1.1.442301.3
		hdc2000c01v1AudPair6FailTrap NOTIFICATION-TYPE
		OBJECTS { trapCounter, hdc2000c01v1Index, hdc2000c01v1AudPair6Fail }
		STATUS current
		DESCRIPTION
			"Audio pair 6 fail Trap"
		::= { hdc2000c01v1Traps 135 }

		-- 1.3.6.1.4.1.10106.2.1.1.442301.3
		hdc2000c01v1AudPair7FailTrap NOTIFICATION-TYPE
		OBJECTS { trapCounter, hdc2000c01v1Index, hdc2000c01v1AudPair7Fail }
		STATUS current
		DESCRIPTION
			"Audio pair 7 fail Trap"
		::= { hdc2000c01v1Traps 137 }

		-- 1.3.6.1.4.1.10106.2.1.1.442301.3
		hdc2000c01v1InFormatTrap NOTIFICATION-TYPE
		OBJECTS { trapCounter, hdc2000c01v1Index, hdc2000c01v1InFormat }
		STATUS current
		DESCRIPTION
			"Input format Trap"
		::= { hdc2000c01v1Traps 139 }

		-- 1.3.6.1.4.1.10106.2.1.1.442301.3
		hdc2000c01v1RefFormatTrap NOTIFICATION-TYPE
		OBJECTS { trapCounter, hdc2000c01v1Index, hdc2000c01v1RefFormat }
		STATUS current
		DESCRIPTION
			"Reference format Trap"
		::= { hdc2000c01v1Traps 141 }

		-- 1.3.6.1.4.1.10106.2.1.1.442701
		gps3002c04v1Traps OBJECT IDENTIFIER ::= { albalaTraps 442701 }

		-- 1.3.6.1.4.1.10106.2.1.1.442701.3
		gps3002c04v1RedundanceModeTrap NOTIFICATION-TYPE
		OBJECTS { trapCounter, gps3002c04v1Index, gps3002c04v1RedundanceMode }
		STATUS current
		DESCRIPTION
			"Allows selecting the redundance mode Trap"
		::= { gps3002c04v1Traps 5 }

		-- 1.3.6.1.4.1.10106.2.1.1.442701.3
		gps3002c04v1HoldoverStatTrap NOTIFICATION-TYPE
		OBJECTS { trapCounter, gps3002c04v1Index, gps3002c04v1HoldoverStat }
		STATUS current
		DESCRIPTION
			"Indicates if the module is locked to GPS or to reference or it is in holdover mode Trap"
		::= { gps3002c04v1Traps 9 }

		-- 1.3.6.1.4.1.10106.2.1.1.442701.3
		gps3002c04v1MaintenanceFailTrap NOTIFICATION-TYPE
		OBJECTS { trapCounter, gps3002c04v1Index, gps3002c04v1MaintenanceFail }
		STATUS current
		DESCRIPTION
			"Indicates that a service operation is required Trap"
		::= { gps3002c04v1Traps 11 }

		-- 1.3.6.1.4.1.10106.2.1.1.442701.3
		gps3002c04v1OutputsMutedTrap NOTIFICATION-TYPE
		OBJECTS { trapCounter, gps3002c04v1Index, gps3002c04v1OutputsMuted }
		STATUS current
		DESCRIPTION
			"Indicates f the module outputs are disabled (reserve module) Trap"
		::= { gps3002c04v1Traps 13 }

		-- 1.3.6.1.4.1.10106.2.1.1.442701.3
		gps3002c04v11ppsDisableTrap NOTIFICATION-TYPE
		OBJECTS { trapCounter, gps3002c04v1Index, gps3002c04v11ppsDisable }
		STATUS current
		DESCRIPTION
			"Indicates if the 1PPS output is muted Trap"
		::= { gps3002c04v1Traps 15 }

		-- 1.3.6.1.4.1.10106.2.1.1.442701.3
		gps3002c04v1AntenaStatTrap NOTIFICATION-TYPE
		OBJECTS { trapCounter, gps3002c04v1Index, gps3002c04v1AntenaStat }
		STATUS current
		DESCRIPTION
			"Antenna connection status Trap"
		::= { gps3002c04v1Traps 21 }

		-- 1.3.6.1.4.1.10106.2.1.1.445101
		hdc2000c02v1Traps OBJECT IDENTIFIER ::= { albalaTraps 445101 }

		-- 1.3.6.1.4.1.10106.2.1.1.445101.3
		hdc2000c02v1AnaRefFmtTrap NOTIFICATION-TYPE
		OBJECTS { trapCounter, hdc2000c02v1Index, hdc2000c02v1AnaRefFmt }
		STATUS current
		DESCRIPTION
			"Analog reference input format Trap"
		::= { hdc2000c02v1Traps 9 }

		-- 1.3.6.1.4.1.10106.2.1.1.445101.3
		hdc2000c02v1ModeConvTrap NOTIFICATION-TYPE
		OBJECTS { trapCounter, hdc2000c02v1Index, hdc2000c02v1ModeConv }
		STATUS current
		DESCRIPTION
			"Conversion mode Trap"
		::= { hdc2000c02v1Traps 15 }

		-- 1.3.6.1.4.1.10106.2.1.1.445101.3
		hdc2000c02v1OutAfdTrap NOTIFICATION-TYPE
		OBJECTS { trapCounter, hdc2000c02v1Index, hdc2000c02v1OutAfd }
		STATUS current
		DESCRIPTION
			"Output active format description Trap"
		::= { hdc2000c02v1Traps 17 }

		-- 1.3.6.1.4.1.10106.2.1.1.445101.3
		hdc2000c02v1OutCfTrap NOTIFICATION-TYPE
		OBJECTS { trapCounter, hdc2000c02v1Index, hdc2000c02v1OutCf }
		STATUS current
		DESCRIPTION
			"Output coded frame Trap"
		::= { hdc2000c02v1Traps 19 }

		-- 1.3.6.1.4.1.10106.2.1.1.445101.3
		hdc2000c02v1InAfdExpctTrap NOTIFICATION-TYPE
		OBJECTS { trapCounter, hdc2000c02v1Index, hdc2000c02v1InAfdExpct }
		STATUS current
		DESCRIPTION
			"Input expected active format description Trap"
		::= { hdc2000c02v1Traps 21 }

		-- 1.3.6.1.4.1.10106.2.1.1.445101.3
		hdc2000c02v1InCfExpctTrap NOTIFICATION-TYPE
		OBJECTS { trapCounter, hdc2000c02v1Index, hdc2000c02v1InCfExpct }
		STATUS current
		DESCRIPTION
			"Input expected coded frame Trap"
		::= { hdc2000c02v1Traps 23 }

		-- 1.3.6.1.4.1.10106.2.1.1.445101.3
		hdc2000c02v1InAfdDetctTrap NOTIFICATION-TYPE
		OBJECTS { trapCounter, hdc2000c02v1Index, hdc2000c02v1InAfdDetct }
		STATUS current
		DESCRIPTION
			"Input detected AFD Trap"
		::= { hdc2000c02v1Traps 93 }

		-- 1.3.6.1.4.1.10106.2.1.1.445101.3
		hdc2000c02v1InCfDetctTrap NOTIFICATION-TYPE
		OBJECTS { trapCounter, hdc2000c02v1Index, hdc2000c02v1InCfDetct }
		STATUS current
		DESCRIPTION
			"Input detected coded frame Trap"
		::= { hdc2000c02v1Traps 95 }

		-- 1.3.6.1.4.1.10106.2.1.1.445101.3
		hdc2000c02v1InPhyFailTrap NOTIFICATION-TYPE
		OBJECTS { trapCounter, hdc2000c02v1Index, hdc2000c02v1InPhyFail }
		STATUS current
		DESCRIPTION
			"Absence fail Trap"
		::= { hdc2000c02v1Traps 97 }

		-- 1.3.6.1.4.1.10106.2.1.1.445101.3
		hdc2000c02v1InFmtFailTrap NOTIFICATION-TYPE
		OBJECTS { trapCounter, hdc2000c02v1Index, hdc2000c02v1InFmtFail }
		STATUS current
		DESCRIPTION
			"Format fail Trap"
		::= { hdc2000c02v1Traps 99 }

		-- 1.3.6.1.4.1.10106.2.1.1.445101.3
		hdc2000c02v1InIncFailTrap NOTIFICATION-TYPE
		OBJECTS { trapCounter, hdc2000c02v1Index, hdc2000c02v1InIncFail }
		STATUS current
		DESCRIPTION
			"Incompatible format fail Trap"
		::= { hdc2000c02v1Traps 101 }

		-- 1.3.6.1.4.1.10106.2.1.1.445101.3
		hdc2000c02v1InCrcFailTrap NOTIFICATION-TYPE
		OBJECTS { trapCounter, hdc2000c02v1Index, hdc2000c02v1InCrcFail }
		STATUS current
		DESCRIPTION
			"EDH/CRC fail Trap"
		::= { hdc2000c02v1Traps 105 }

		-- 1.3.6.1.4.1.10106.2.1.1.445101.3
		hdc2000c02v1PresAudG1FailTrap NOTIFICATION-TYPE
		OBJECTS { trapCounter, hdc2000c02v1Index, hdc2000c02v1PresAudG1Fail }
		STATUS current
		DESCRIPTION
			"Audio group 1 presence fail Trap"
		::= { hdc2000c02v1Traps 115 }

		-- 1.3.6.1.4.1.10106.2.1.1.445101.3
		hdc2000c02v1PresAudG2FailTrap NOTIFICATION-TYPE
		OBJECTS { trapCounter, hdc2000c02v1Index, hdc2000c02v1PresAudG2Fail }
		STATUS current
		DESCRIPTION
			"Audio group 2 presence fail Trap"
		::= { hdc2000c02v1Traps 117 }

		-- 1.3.6.1.4.1.10106.2.1.1.445101.3
		hdc2000c02v1PresAudG3FailTrap NOTIFICATION-TYPE
		OBJECTS { trapCounter, hdc2000c02v1Index, hdc2000c02v1PresAudG3Fail }
		STATUS current
		DESCRIPTION
			"Audio group 3 presence fail Trap"
		::= { hdc2000c02v1Traps 119 }

		-- 1.3.6.1.4.1.10106.2.1.1.445101.3
		hdc2000c02v1PresAudG4FailTrap NOTIFICATION-TYPE
		OBJECTS { trapCounter, hdc2000c02v1Index, hdc2000c02v1PresAudG4Fail }
		STATUS current
		DESCRIPTION
			"Audio group 4 presence fail Trap"
		::= { hdc2000c02v1Traps 121 }

		-- 1.3.6.1.4.1.10106.2.1.1.445101.3
		hdc2000c02v1RefFailTrap NOTIFICATION-TYPE
		OBJECTS { trapCounter, hdc2000c02v1Index, hdc2000c02v1RefFail }
		STATUS current
		DESCRIPTION
			"Analog reference absence fail Trap"
		::= { hdc2000c02v1Traps 123 }

		-- 1.3.6.1.4.1.10106.2.1.1.445101.3
		hdc2000c02v1RefFmtFailTrap NOTIFICATION-TYPE
		OBJECTS { trapCounter, hdc2000c02v1Index, hdc2000c02v1RefFmtFail }
		STATUS current
		DESCRIPTION
			"Analog reference format fail Trap"
		::= { hdc2000c02v1Traps 125 }

		-- 1.3.6.1.4.1.10106.2.1.1.445101.3
		hdc2000c02v1LockFailTrap NOTIFICATION-TYPE
		OBJECTS { trapCounter, hdc2000c02v1Index, hdc2000c02v1LockFail }
		STATUS current
		DESCRIPTION
			"Reference unlock fail Trap"
		::= { hdc2000c02v1Traps 127 }

		-- 1.3.6.1.4.1.10106.2.1.1.445101.3
		hdc2000c02v1AudPair0FailTrap NOTIFICATION-TYPE
		OBJECTS { trapCounter, hdc2000c02v1Index, hdc2000c02v1AudPair0Fail }
		STATUS current
		DESCRIPTION
			"Audio pair 0 fail Trap"
		::= { hdc2000c02v1Traps 129 }

		-- 1.3.6.1.4.1.10106.2.1.1.445101.3
		hdc2000c02v1AudPair1FailTrap NOTIFICATION-TYPE
		OBJECTS { trapCounter, hdc2000c02v1Index, hdc2000c02v1AudPair1Fail }
		STATUS current
		DESCRIPTION
			"Audio pair 1 fail Trap"
		::= { hdc2000c02v1Traps 131 }

		-- 1.3.6.1.4.1.10106.2.1.1.445101.3
		hdc2000c02v1AudPair2FailTrap NOTIFICATION-TYPE
		OBJECTS { trapCounter, hdc2000c02v1Index, hdc2000c02v1AudPair2Fail }
		STATUS current
		DESCRIPTION
			"Audio pair 2 fail Trap"
		::= { hdc2000c02v1Traps 133 }

		-- 1.3.6.1.4.1.10106.2.1.1.445101.3
		hdc2000c02v1AudPair3FailTrap NOTIFICATION-TYPE
		OBJECTS { trapCounter, hdc2000c02v1Index, hdc2000c02v1AudPair3Fail }
		STATUS current
		DESCRIPTION
			"Audio pair 3 fail Trap"
		::= { hdc2000c02v1Traps 135 }

		-- 1.3.6.1.4.1.10106.2.1.1.445101.3
		hdc2000c02v1AudPair4FailTrap NOTIFICATION-TYPE
		OBJECTS { trapCounter, hdc2000c02v1Index, hdc2000c02v1AudPair4Fail }
		STATUS current
		DESCRIPTION
			"Audio pair 4 fail Trap"
		::= { hdc2000c02v1Traps 137 }

		-- 1.3.6.1.4.1.10106.2.1.1.445101.3
		hdc2000c02v1AudPair5FailTrap NOTIFICATION-TYPE
		OBJECTS { trapCounter, hdc2000c02v1Index, hdc2000c02v1AudPair5Fail }
		STATUS current
		DESCRIPTION
			"Audio pair 5 fail Trap"
		::= { hdc2000c02v1Traps 139 }

		-- 1.3.6.1.4.1.10106.2.1.1.445101.3
		hdc2000c02v1AudPair6FailTrap NOTIFICATION-TYPE
		OBJECTS { trapCounter, hdc2000c02v1Index, hdc2000c02v1AudPair6Fail }
		STATUS current
		DESCRIPTION
			"Audio pair 6 fail Trap"
		::= { hdc2000c02v1Traps 141 }

		-- 1.3.6.1.4.1.10106.2.1.1.445101.3
		hdc2000c02v1AudPair7FailTrap NOTIFICATION-TYPE
		OBJECTS { trapCounter, hdc2000c02v1Index, hdc2000c02v1AudPair7Fail }
		STATUS current
		DESCRIPTION
			"Audio pair 7 fail Trap"
		::= { hdc2000c02v1Traps 143 }

		-- 1.3.6.1.4.1.10106.2.1.1.445101.3
		hdc2000c02v1InFormatTrap NOTIFICATION-TYPE
		OBJECTS { trapCounter, hdc2000c02v1Index, hdc2000c02v1InFormat }
		STATUS current
		DESCRIPTION
			"Input format Trap"
		::= { hdc2000c02v1Traps 145 }

		-- 1.3.6.1.4.1.10106.2.1.1.445101.3
		hdc2000c02v1RefFormatTrap NOTIFICATION-TYPE
		OBJECTS { trapCounter, hdc2000c02v1Index, hdc2000c02v1RefFormat }
		STATUS current
		DESCRIPTION
			"Reference format Trap"
		::= { hdc2000c02v1Traps 147 }

		-- 1.3.6.1.4.1.10106.2.1.1.446901
		hxc3000c01v1Traps OBJECT IDENTIFIER ::= { albalaTraps 446901 }

		-- 1.3.6.1.4.1.10106.2.1.1.446901.3
		hxc3000c01v1AnaRefFmtTrap NOTIFICATION-TYPE
		OBJECTS { trapCounter, hxc3000c01v1Index, hxc3000c01v1AnaRefFmt }
		STATUS current
		DESCRIPTION
			"Analog reference input format Trap"
		::= { hxc3000c01v1Traps 9 }

		-- 1.3.6.1.4.1.10106.2.1.1.446901.3
		hxc3000c01v1ModeConvTrap NOTIFICATION-TYPE
		OBJECTS { trapCounter, hxc3000c01v1Index, hxc3000c01v1ModeConv }
		STATUS current
		DESCRIPTION
			"Conversion mode Trap"
		::= { hxc3000c01v1Traps 17 }

		-- 1.3.6.1.4.1.10106.2.1.1.446901.3
		hxc3000c01v1OutAfdTrap NOTIFICATION-TYPE
		OBJECTS { trapCounter, hxc3000c01v1Index, hxc3000c01v1OutAfd }
		STATUS current
		DESCRIPTION
			"Output active format description Trap"
		::= { hxc3000c01v1Traps 19 }

		-- 1.3.6.1.4.1.10106.2.1.1.446901.3
		hxc3000c01v1OutCfTrap NOTIFICATION-TYPE
		OBJECTS { trapCounter, hxc3000c01v1Index, hxc3000c01v1OutCf }
		STATUS current
		DESCRIPTION
			"Output coded frame Trap"
		::= { hxc3000c01v1Traps 21 }

		-- 1.3.6.1.4.1.10106.2.1.1.446901.3
		hxc3000c01v1InAfdExpctTrap NOTIFICATION-TYPE
		OBJECTS { trapCounter, hxc3000c01v1Index, hxc3000c01v1InAfdExpct }
		STATUS current
		DESCRIPTION
			"Input expected active format description Trap"
		::= { hxc3000c01v1Traps 25 }

		-- 1.3.6.1.4.1.10106.2.1.1.446901.3
		hxc3000c01v1InCfExpctTrap NOTIFICATION-TYPE
		OBJECTS { trapCounter, hxc3000c01v1Index, hxc3000c01v1InCfExpct }
		STATUS current
		DESCRIPTION
			"Input expected coded frame Trap"
		::= { hxc3000c01v1Traps 27 }

		-- 1.3.6.1.4.1.10106.2.1.1.446901.3
		hxc3000c01v1TxFmtTrap NOTIFICATION-TYPE
		OBJECTS { trapCounter, hxc3000c01v1Index, hxc3000c01v1TxFmt }
		STATUS current
		DESCRIPTION
			"Output format Trap"
		::= { hxc3000c01v1Traps 29 }

		-- 1.3.6.1.4.1.10106.2.1.1.446901.3
		hxc3000c01v1DeintAlgorithmTrap NOTIFICATION-TYPE
		OBJECTS { trapCounter, hxc3000c01v1Index, hxc3000c01v1DeintAlgorithm }
		STATUS current
		DESCRIPTION
			"Allows selecting the de-interlacing algorithm Trap"
		::= { hxc3000c01v1Traps 31 }

		-- 1.3.6.1.4.1.10106.2.1.1.446901.3
		hxc3000c01v1InPhyFailTrap NOTIFICATION-TYPE
		OBJECTS { trapCounter, hxc3000c01v1Index, hxc3000c01v1InPhyFail }
		STATUS current
		DESCRIPTION
			"Absence fail Trap"
		::= { hxc3000c01v1Traps 101 }

		-- 1.3.6.1.4.1.10106.2.1.1.446901.3
		hxc3000c01v1InFmtFailTrap NOTIFICATION-TYPE
		OBJECTS { trapCounter, hxc3000c01v1Index, hxc3000c01v1InFmtFail }
		STATUS current
		DESCRIPTION
			"Format fail Trap"
		::= { hxc3000c01v1Traps 103 }

		-- 1.3.6.1.4.1.10106.2.1.1.446901.3
		hxc3000c01v1InIncFailTrap NOTIFICATION-TYPE
		OBJECTS { trapCounter, hxc3000c01v1Index, hxc3000c01v1InIncFail }
		STATUS current
		DESCRIPTION
			"Incompatible format fail Trap"
		::= { hxc3000c01v1Traps 105 }

		-- 1.3.6.1.4.1.10106.2.1.1.446901.3
		hxc3000c01v1InCrcFailTrap NOTIFICATION-TYPE
		OBJECTS { trapCounter, hxc3000c01v1Index, hxc3000c01v1InCrcFail }
		STATUS current
		DESCRIPTION
			"EDH/CRC fail Trap"
		::= { hxc3000c01v1Traps 109 }

		-- 1.3.6.1.4.1.10106.2.1.1.446901.3
		hxc3000c01v1PresAudG1FailTrap NOTIFICATION-TYPE
		OBJECTS { trapCounter, hxc3000c01v1Index, hxc3000c01v1PresAudG1Fail }
		STATUS current
		DESCRIPTION
			"Audio group 1 presence fail Trap"
		::= { hxc3000c01v1Traps 119 }

		-- 1.3.6.1.4.1.10106.2.1.1.446901.3
		hxc3000c01v1PresAudG2FailTrap NOTIFICATION-TYPE
		OBJECTS { trapCounter, hxc3000c01v1Index, hxc3000c01v1PresAudG2Fail }
		STATUS current
		DESCRIPTION
			"Audio group 2 presence fail Trap"
		::= { hxc3000c01v1Traps 121 }

		-- 1.3.6.1.4.1.10106.2.1.1.446901.3
		hxc3000c01v1PresAudG3FailTrap NOTIFICATION-TYPE
		OBJECTS { trapCounter, hxc3000c01v1Index, hxc3000c01v1PresAudG3Fail }
		STATUS current
		DESCRIPTION
			"Audio group 3 presence fail Trap"
		::= { hxc3000c01v1Traps 123 }

		-- 1.3.6.1.4.1.10106.2.1.1.446901.3
		hxc3000c01v1PresAudG4FailTrap NOTIFICATION-TYPE
		OBJECTS { trapCounter, hxc3000c01v1Index, hxc3000c01v1PresAudG4Fail }
		STATUS current
		DESCRIPTION
			"Audio group 4 presence fail Trap"
		::= { hxc3000c01v1Traps 125 }

		-- 1.3.6.1.4.1.10106.2.1.1.446901.3
		hxc3000c01v1RefFailTrap NOTIFICATION-TYPE
		OBJECTS { trapCounter, hxc3000c01v1Index, hxc3000c01v1RefFail }
		STATUS current
		DESCRIPTION
			"Analog reference absence fail Trap"
		::= { hxc3000c01v1Traps 127 }

		-- 1.3.6.1.4.1.10106.2.1.1.446901.3
		hxc3000c01v1RefFmtFailTrap NOTIFICATION-TYPE
		OBJECTS { trapCounter, hxc3000c01v1Index, hxc3000c01v1RefFmtFail }
		STATUS current
		DESCRIPTION
			"Analog reference format fail Trap"
		::= { hxc3000c01v1Traps 129 }

		-- 1.3.6.1.4.1.10106.2.1.1.446901.3
		hxc3000c01v1LockFailTrap NOTIFICATION-TYPE
		OBJECTS { trapCounter, hxc3000c01v1Index, hxc3000c01v1LockFail }
		STATUS current
		DESCRIPTION
			"Reference unlock fail Trap"
		::= { hxc3000c01v1Traps 131 }

		-- 1.3.6.1.4.1.10106.2.1.1.446901.3
		hxc3000c01v1AudPair0FailTrap NOTIFICATION-TYPE
		OBJECTS { trapCounter, hxc3000c01v1Index, hxc3000c01v1AudPair0Fail }
		STATUS current
		DESCRIPTION
			"Audio pair 0 fail Trap"
		::= { hxc3000c01v1Traps 133 }

		-- 1.3.6.1.4.1.10106.2.1.1.446901.3
		hxc3000c01v1AudPair1FailTrap NOTIFICATION-TYPE
		OBJECTS { trapCounter, hxc3000c01v1Index, hxc3000c01v1AudPair1Fail }
		STATUS current
		DESCRIPTION
			"Audio pair 1 fail Trap"
		::= { hxc3000c01v1Traps 135 }

		-- 1.3.6.1.4.1.10106.2.1.1.446901.3
		hxc3000c01v1AudPair2FailTrap NOTIFICATION-TYPE
		OBJECTS { trapCounter, hxc3000c01v1Index, hxc3000c01v1AudPair2Fail }
		STATUS current
		DESCRIPTION
			"Audio pair 2 fail Trap"
		::= { hxc3000c01v1Traps 137 }

		-- 1.3.6.1.4.1.10106.2.1.1.446901.3
		hxc3000c01v1AudPair3FailTrap NOTIFICATION-TYPE
		OBJECTS { trapCounter, hxc3000c01v1Index, hxc3000c01v1AudPair3Fail }
		STATUS current
		DESCRIPTION
			"Audio pair 3 fail Trap"
		::= { hxc3000c01v1Traps 139 }

		-- 1.3.6.1.4.1.10106.2.1.1.446901.3
		hxc3000c01v1AudPair4FailTrap NOTIFICATION-TYPE
		OBJECTS { trapCounter, hxc3000c01v1Index, hxc3000c01v1AudPair4Fail }
		STATUS current
		DESCRIPTION
			"Audio pair 4 fail Trap"
		::= { hxc3000c01v1Traps 141 }

		-- 1.3.6.1.4.1.10106.2.1.1.446901.3
		hxc3000c01v1AudPair5FailTrap NOTIFICATION-TYPE
		OBJECTS { trapCounter, hxc3000c01v1Index, hxc3000c01v1AudPair5Fail }
		STATUS current
		DESCRIPTION
			"Audio pair 5 fail Trap"
		::= { hxc3000c01v1Traps 143 }

		-- 1.3.6.1.4.1.10106.2.1.1.446901.3
		hxc3000c01v1AudPair6FailTrap NOTIFICATION-TYPE
		OBJECTS { trapCounter, hxc3000c01v1Index, hxc3000c01v1AudPair6Fail }
		STATUS current
		DESCRIPTION
			"Audio pair 6 fail Trap"
		::= { hxc3000c01v1Traps 145 }

		-- 1.3.6.1.4.1.10106.2.1.1.446901.3
		hxc3000c01v1AudPair7FailTrap NOTIFICATION-TYPE
		OBJECTS { trapCounter, hxc3000c01v1Index, hxc3000c01v1AudPair7Fail }
		STATUS current
		DESCRIPTION
			"Audio pair 7 fail Trap"
		::= { hxc3000c01v1Traps 147 }

		-- 1.3.6.1.4.1.10106.2.1.1.446901.3
		hxc3000c01v1InAfdDetctTrap NOTIFICATION-TYPE
		OBJECTS { trapCounter, hxc3000c01v1Index, hxc3000c01v1InAfdDetct }
		STATUS current
		DESCRIPTION
			"Input detected AFD Trap"
		::= { hxc3000c01v1Traps 149 }

		-- 1.3.6.1.4.1.10106.2.1.1.446901.3
		hxc3000c01v1InCfDetctTrap NOTIFICATION-TYPE
		OBJECTS { trapCounter, hxc3000c01v1Index, hxc3000c01v1InCfDetct }
		STATUS current
		DESCRIPTION
			"Input detected coded frame Trap"
		::= { hxc3000c01v1Traps 151 }

		-- 1.3.6.1.4.1.10106.2.1.1.446901.3
		hxc3000c01v1InFormatTrap NOTIFICATION-TYPE
		OBJECTS { trapCounter, hxc3000c01v1Index, hxc3000c01v1InFormat }
		STATUS current
		DESCRIPTION
			"Input format Trap"
		::= { hxc3000c01v1Traps 153 }

		-- 1.3.6.1.4.1.10106.2.1.1.446901.3
		hxc3000c01v1RefFormatTrap NOTIFICATION-TYPE
		OBJECTS { trapCounter, hxc3000c01v1Index, hxc3000c01v1RefFormat }
		STATUS current
		DESCRIPTION
			"Reference format Trap"
		::= { hxc3000c01v1Traps 155 }

		-- 1.3.6.1.4.1.10106.2.1.1.446901.3
		hxc3000c01v1TxFormatTrap NOTIFICATION-TYPE
		OBJECTS { trapCounter, hxc3000c01v1Index, hxc3000c01v1TxFormat }
		STATUS current
		DESCRIPTION
			"Output format Trap"
		::= { hxc3000c01v1Traps 157 }

		-- 1.3.6.1.4.1.10106.2.1.1.454401
		hsw2000c01v1Traps OBJECT IDENTIFIER ::= { albalaTraps 454401 }

		-- 1.3.6.1.4.1.10106.2.1.1.454401.3
		hsw2000c01v1StateSelTrap NOTIFICATION-TYPE
		OBJECTS { trapCounter, hsw2000c01v1Index, hsw2000c01v1StateSel }
		STATUS current
		DESCRIPTION
			"Shows the module's current state Trap"
		::= { hsw2000c01v1Traps 9 }

		-- 1.3.6.1.4.1.10106.2.1.1.454401.3
		hsw2000c01v1SwitchModeTrap NOTIFICATION-TYPE
		OBJECTS { trapCounter, hsw2000c01v1Index, hsw2000c01v1SwitchMode }
		STATUS current
		DESCRIPTION
			"Allows selecting the switching mode Trap"
		::= { hsw2000c01v1Traps 11 }

		-- 1.3.6.1.4.1.10106.2.1.1.454401.3
		hsw2000c01v1BypassEnableTrap NOTIFICATION-TYPE
		OBJECTS { trapCounter, hsw2000c01v1Index, hsw2000c01v1BypassEnable }
		STATUS current
		DESCRIPTION
			"Allows activating the rear board bypass Trap"
		::= { hsw2000c01v1Traps 15 }

		-- 1.3.6.1.4.1.10106.2.1.1.454401.3
		hsw2000c01v1In1FailTrap NOTIFICATION-TYPE
		OBJECTS { trapCounter, hsw2000c01v1Index, hsw2000c01v1In1Fail }
		STATUS current
		DESCRIPTION
			"Input 1 fail Trap"
		::= { hsw2000c01v1Traps 175 }

		-- 1.3.6.1.4.1.10106.2.1.1.454401.3
		hsw2000c01v1In2FailTrap NOTIFICATION-TYPE
		OBJECTS { trapCounter, hsw2000c01v1Index, hsw2000c01v1In2Fail }
		STATUS current
		DESCRIPTION
			"Input 2 fail Trap"
		::= { hsw2000c01v1Traps 177 }

		-- 1.3.6.1.4.1.10106.2.1.1.454401.3
		hsw2000c01v1EqualPidTrap NOTIFICATION-TYPE
		OBJECTS { trapCounter, hsw2000c01v1Index, hsw2000c01v1EqualPid }
		STATUS current
		DESCRIPTION
			"Indicates if both  inputs have same PID Trap"
		::= { hsw2000c01v1Traps 179 }

		-- 1.3.6.1.4.1.10106.2.1.1.454401.3
		hsw2000c01v1SelOut1Trap NOTIFICATION-TYPE
		OBJECTS { trapCounter, hsw2000c01v1Index, hsw2000c01v1SelOut1 }
		STATUS current
		DESCRIPTION
			"Output 1 Trap"
		::= { hsw2000c01v1Traps 181 }

		-- 1.3.6.1.4.1.10106.2.1.1.454401.3
		hsw2000c01v1SelOut2Trap NOTIFICATION-TYPE
		OBJECTS { trapCounter, hsw2000c01v1Index, hsw2000c01v1SelOut2 }
		STATUS current
		DESCRIPTION
			"Output 2 Trap"
		::= { hsw2000c01v1Traps 183 }

		-- 1.3.6.1.4.1.10106.2.1.1.454401.3
		hsw2000c01v1EqualUmidTrap NOTIFICATION-TYPE
		OBJECTS { trapCounter, hsw2000c01v1Index, hsw2000c01v1EqualUmid }
		STATUS current
		DESCRIPTION
			"Indicates if both  inputs have same UMID Trap"
		::= { hsw2000c01v1Traps 185 }

		-- 1.3.6.1.4.1.10106.2.1.1.454401.3
		hsw2000c01v1In1PhyFailTrap NOTIFICATION-TYPE
		OBJECTS { trapCounter, hsw2000c01v1Index, hsw2000c01v1In1PhyFail }
		STATUS current
		DESCRIPTION
			"Absence fail Trap"
		::= { hsw2000c01v1Traps 187 }

		-- 1.3.6.1.4.1.10106.2.1.1.454401.3
		hsw2000c01v1In1FmtFailTrap NOTIFICATION-TYPE
		OBJECTS { trapCounter, hsw2000c01v1Index, hsw2000c01v1In1FmtFail }
		STATUS current
		DESCRIPTION
			"Format fail Trap"
		::= { hsw2000c01v1Traps 189 }

		-- 1.3.6.1.4.1.10106.2.1.1.454401.3
		hsw2000c01v1In1IncFailTrap NOTIFICATION-TYPE
		OBJECTS { trapCounter, hsw2000c01v1Index, hsw2000c01v1In1IncFail }
		STATUS current
		DESCRIPTION
			"Incompatible format fail Trap"
		::= { hsw2000c01v1Traps 191 }

		-- 1.3.6.1.4.1.10106.2.1.1.454401.3
		hsw2000c01v1In1BlkFailTrap NOTIFICATION-TYPE
		OBJECTS { trapCounter, hsw2000c01v1Index, hsw2000c01v1In1BlkFail }
		STATUS current
		DESCRIPTION
			"Black signal fail Trap"
		::= { hsw2000c01v1Traps 193 }

		-- 1.3.6.1.4.1.10106.2.1.1.454401.3
		hsw2000c01v1In1FrzFailTrap NOTIFICATION-TYPE
		OBJECTS { trapCounter, hsw2000c01v1Index, hsw2000c01v1In1FrzFail }
		STATUS current
		DESCRIPTION
			"Freeze signal fail Trap"
		::= { hsw2000c01v1Traps 195 }

		-- 1.3.6.1.4.1.10106.2.1.1.454401.3
		hsw2000c01v1In1PatFailTrap NOTIFICATION-TYPE
		OBJECTS { trapCounter, hsw2000c01v1Index, hsw2000c01v1In1PatFail }
		STATUS current
		DESCRIPTION
			"Video pattern fail Trap"
		::= { hsw2000c01v1Traps 197 }

		-- 1.3.6.1.4.1.10106.2.1.1.454401.3
		hsw2000c01v1In1CrcFailTrap NOTIFICATION-TYPE
		OBJECTS { trapCounter, hsw2000c01v1Index, hsw2000c01v1In1CrcFail }
		STATUS current
		DESCRIPTION
			"EDH/CRC fail Trap"
		::= { hsw2000c01v1Traps 199 }

		-- 1.3.6.1.4.1.10106.2.1.1.454401.3
		hsw2000c01v1In1SilFailTrap NOTIFICATION-TYPE
		OBJECTS { trapCounter, hsw2000c01v1Index, hsw2000c01v1In1SilFail }
		STATUS current
		DESCRIPTION
			"Audio silence fail Trap"
		::= { hsw2000c01v1Traps 201 }

		-- 1.3.6.1.4.1.10106.2.1.1.454401.3
		hsw2000c01v1In1OvrFailTrap NOTIFICATION-TYPE
		OBJECTS { trapCounter, hsw2000c01v1Index, hsw2000c01v1In1OvrFail }
		STATUS current
		DESCRIPTION
			"Audio overload fail Trap"
		::= { hsw2000c01v1Traps 203 }

		-- 1.3.6.1.4.1.10106.2.1.1.454401.3
		hsw2000c01v1In1PhFailTrap NOTIFICATION-TYPE
		OBJECTS { trapCounter, hsw2000c01v1Index, hsw2000c01v1In1PhFail }
		STATUS current
		DESCRIPTION
			"Audio phase fail Trap"
		::= { hsw2000c01v1Traps 205 }

		-- 1.3.6.1.4.1.10106.2.1.1.454401.3
		hsw2000c01v1In1PreFailTrap NOTIFICATION-TYPE
		OBJECTS { trapCounter, hsw2000c01v1Index, hsw2000c01v1In1PreFail }
		STATUS current
		DESCRIPTION
			"Audio presence fail Trap"
		::= { hsw2000c01v1Traps 207 }

		-- 1.3.6.1.4.1.10106.2.1.1.454401.3
		hsw2000c01v1In2PhyFailTrap NOTIFICATION-TYPE
		OBJECTS { trapCounter, hsw2000c01v1Index, hsw2000c01v1In2PhyFail }
		STATUS current
		DESCRIPTION
			"Absence fail Trap"
		::= { hsw2000c01v1Traps 209 }

		-- 1.3.6.1.4.1.10106.2.1.1.454401.3
		hsw2000c01v1In2FmtFailTrap NOTIFICATION-TYPE
		OBJECTS { trapCounter, hsw2000c01v1Index, hsw2000c01v1In2FmtFail }
		STATUS current
		DESCRIPTION
			"Format fail Trap"
		::= { hsw2000c01v1Traps 211 }

		-- 1.3.6.1.4.1.10106.2.1.1.454401.3
		hsw2000c01v1In2IncFailTrap NOTIFICATION-TYPE
		OBJECTS { trapCounter, hsw2000c01v1Index, hsw2000c01v1In2IncFail }
		STATUS current
		DESCRIPTION
			"Incompatible format fail Trap"
		::= { hsw2000c01v1Traps 213 }

		-- 1.3.6.1.4.1.10106.2.1.1.454401.3
		hsw2000c01v1In2BlkFailTrap NOTIFICATION-TYPE
		OBJECTS { trapCounter, hsw2000c01v1Index, hsw2000c01v1In2BlkFail }
		STATUS current
		DESCRIPTION
			"Black signal fail Trap"
		::= { hsw2000c01v1Traps 215 }

		-- 1.3.6.1.4.1.10106.2.1.1.454401.3
		hsw2000c01v1In2FrzFailTrap NOTIFICATION-TYPE
		OBJECTS { trapCounter, hsw2000c01v1Index, hsw2000c01v1In2FrzFail }
		STATUS current
		DESCRIPTION
			"Freeze signal fail Trap"
		::= { hsw2000c01v1Traps 217 }

		-- 1.3.6.1.4.1.10106.2.1.1.454401.3
		hsw2000c01v1In2PatFailTrap NOTIFICATION-TYPE
		OBJECTS { trapCounter, hsw2000c01v1Index, hsw2000c01v1In2PatFail }
		STATUS current
		DESCRIPTION
			"Video pattern fail Trap"
		::= { hsw2000c01v1Traps 219 }

		-- 1.3.6.1.4.1.10106.2.1.1.454401.3
		hsw2000c01v1In2CrcFailTrap NOTIFICATION-TYPE
		OBJECTS { trapCounter, hsw2000c01v1Index, hsw2000c01v1In2CrcFail }
		STATUS current
		DESCRIPTION
			"EDH/CRC fail Trap"
		::= { hsw2000c01v1Traps 221 }

		-- 1.3.6.1.4.1.10106.2.1.1.454401.3
		hsw2000c01v1In2SilFailTrap NOTIFICATION-TYPE
		OBJECTS { trapCounter, hsw2000c01v1Index, hsw2000c01v1In2SilFail }
		STATUS current
		DESCRIPTION
			"Audio silence fail Trap"
		::= { hsw2000c01v1Traps 223 }

		-- 1.3.6.1.4.1.10106.2.1.1.454401.3
		hsw2000c01v1In2OvrFailTrap NOTIFICATION-TYPE
		OBJECTS { trapCounter, hsw2000c01v1Index, hsw2000c01v1In2OvrFail }
		STATUS current
		DESCRIPTION
			"Audio overload fail Trap"
		::= { hsw2000c01v1Traps 225 }

		-- 1.3.6.1.4.1.10106.2.1.1.454401.3
		hsw2000c01v1In2PhFailTrap NOTIFICATION-TYPE
		OBJECTS { trapCounter, hsw2000c01v1Index, hsw2000c01v1In2PhFail }
		STATUS current
		DESCRIPTION
			"Audio phase fail Trap"
		::= { hsw2000c01v1Traps 227 }

		-- 1.3.6.1.4.1.10106.2.1.1.454401.3
		hsw2000c01v1In2PreFailTrap NOTIFICATION-TYPE
		OBJECTS { trapCounter, hsw2000c01v1Index, hsw2000c01v1In2PreFail }
		STATUS current
		DESCRIPTION
			"Audio presence fail Trap"
		::= { hsw2000c01v1Traps 229 }

		-- 1.3.6.1.4.1.10106.2.1.1.454401.3
		hsw2000c01v1RefFailTrap NOTIFICATION-TYPE
		OBJECTS { trapCounter, hsw2000c01v1Index, hsw2000c01v1RefFail }
		STATUS current
		DESCRIPTION
			"Reference absence fail Trap"
		::= { hsw2000c01v1Traps 231 }

		-- 1.3.6.1.4.1.10106.2.1.1.454401.3
		hsw2000c01v1LockFailTrap NOTIFICATION-TYPE
		OBJECTS { trapCounter, hsw2000c01v1Index, hsw2000c01v1LockFail }
		STATUS current
		DESCRIPTION
			"Reference unlock fail Trap"
		::= { hsw2000c01v1Traps 233 }

		-- 1.3.6.1.4.1.10106.2.1.1.454401.3
		hsw2000c01v1In1FormatTrap NOTIFICATION-TYPE
		OBJECTS { trapCounter, hsw2000c01v1Index, hsw2000c01v1In1Format }
		STATUS current
		DESCRIPTION
			"Input format Trap"
		::= { hsw2000c01v1Traps 235 }

		-- 1.3.6.1.4.1.10106.2.1.1.454401.3
		hsw2000c01v1In2FormatTrap NOTIFICATION-TYPE
		OBJECTS { trapCounter, hsw2000c01v1Index, hsw2000c01v1In2Format }
		STATUS current
		DESCRIPTION
			"Input format Trap"
		::= { hsw2000c01v1Traps 237 }

		-- 1.3.6.1.4.1.10106.2.1.1.454401.3
		hsw2000c01v1RefFormatTrap NOTIFICATION-TYPE
		OBJECTS { trapCounter, hsw2000c01v1Index, hsw2000c01v1RefFormat }
		STATUS current
		DESCRIPTION
			"Reference format Trap"
		::= { hsw2000c01v1Traps 239 }

		-- 1.3.6.1.4.1.10106.2.1.1.454401.3
		hsw2000c01v1In1Grp1PresTrap NOTIFICATION-TYPE
		OBJECTS { trapCounter, hsw2000c01v1Index, hsw2000c01v1In1Grp1Pres }
		STATUS current
		DESCRIPTION
			"Audio group 1 packet presence Trap"
		::= { hsw2000c01v1Traps 249 }

		-- 1.3.6.1.4.1.10106.2.1.1.454401.3
		hsw2000c01v1In1Grp2PresTrap NOTIFICATION-TYPE
		OBJECTS { trapCounter, hsw2000c01v1Index, hsw2000c01v1In1Grp2Pres }
		STATUS current
		DESCRIPTION
			"Audio group 2 packet presence Trap"
		::= { hsw2000c01v1Traps 251 }

		-- 1.3.6.1.4.1.10106.2.1.1.454401.3
		hsw2000c01v1In1Grp3PresTrap NOTIFICATION-TYPE
		OBJECTS { trapCounter, hsw2000c01v1Index, hsw2000c01v1In1Grp3Pres }
		STATUS current
		DESCRIPTION
			"Audio group 3 packet presence Trap"
		::= { hsw2000c01v1Traps 253 }

		-- 1.3.6.1.4.1.10106.2.1.1.454401.3
		hsw2000c01v1In1Grp4PresTrap NOTIFICATION-TYPE
		OBJECTS { trapCounter, hsw2000c01v1Index, hsw2000c01v1In1Grp4Pres }
		STATUS current
		DESCRIPTION
			"Audio group 4 packet presence Trap"
		::= { hsw2000c01v1Traps 255 }

		-- 1.3.6.1.4.1.10106.2.1.1.454401.3
		hsw2000c01v1In1Grp1P0StatTrap NOTIFICATION-TYPE
		OBJECTS { trapCounter, hsw2000c01v1Index, hsw2000c01v1In1Grp1P0Stat }
		STATUS current
		DESCRIPTION
			"Audio group 1 pair 0 status Trap"
		::= { hsw2000c01v1Traps 257 }

		-- 1.3.6.1.4.1.10106.2.1.1.454401.3
		hsw2000c01v1In1Grp1P1StatTrap NOTIFICATION-TYPE
		OBJECTS { trapCounter, hsw2000c01v1Index, hsw2000c01v1In1Grp1P1Stat }
		STATUS current
		DESCRIPTION
			"Audio group 1 pair 1 status Trap"
		::= { hsw2000c01v1Traps 259 }

		-- 1.3.6.1.4.1.10106.2.1.1.454401.3
		hsw2000c01v1In1Grp2P0StatTrap NOTIFICATION-TYPE
		OBJECTS { trapCounter, hsw2000c01v1Index, hsw2000c01v1In1Grp2P0Stat }
		STATUS current
		DESCRIPTION
			"Audio group 2 pair 0 status Trap"
		::= { hsw2000c01v1Traps 261 }

		-- 1.3.6.1.4.1.10106.2.1.1.454401.3
		hsw2000c01v1In1Grp2P1StatTrap NOTIFICATION-TYPE
		OBJECTS { trapCounter, hsw2000c01v1Index, hsw2000c01v1In1Grp2P1Stat }
		STATUS current
		DESCRIPTION
			"Audio group 2 pair 1 status Trap"
		::= { hsw2000c01v1Traps 263 }

		-- 1.3.6.1.4.1.10106.2.1.1.454401.3
		hsw2000c01v1In1Grp3P0StatTrap NOTIFICATION-TYPE
		OBJECTS { trapCounter, hsw2000c01v1Index, hsw2000c01v1In1Grp3P0Stat }
		STATUS current
		DESCRIPTION
			"Audio group 3 pair 0 status Trap"
		::= { hsw2000c01v1Traps 265 }

		-- 1.3.6.1.4.1.10106.2.1.1.454401.3
		hsw2000c01v1In1Grp3P1StatTrap NOTIFICATION-TYPE
		OBJECTS { trapCounter, hsw2000c01v1Index, hsw2000c01v1In1Grp3P1Stat }
		STATUS current
		DESCRIPTION
			"Audio group 3 pair 1 status Trap"
		::= { hsw2000c01v1Traps 267 }

		-- 1.3.6.1.4.1.10106.2.1.1.454401.3
		hsw2000c01v1In1Grp4P0StatTrap NOTIFICATION-TYPE
		OBJECTS { trapCounter, hsw2000c01v1Index, hsw2000c01v1In1Grp4P0Stat }
		STATUS current
		DESCRIPTION
			"Audio group 4 pair 0 status Trap"
		::= { hsw2000c01v1Traps 269 }

		-- 1.3.6.1.4.1.10106.2.1.1.454401.3
		hsw2000c01v1In1Grp4P1StatTrap NOTIFICATION-TYPE
		OBJECTS { trapCounter, hsw2000c01v1Index, hsw2000c01v1In1Grp4P1Stat }
		STATUS current
		DESCRIPTION
			"Audio group 4 pair 1 status Trap"
		::= { hsw2000c01v1Traps 271 }

		-- 1.3.6.1.4.1.10106.2.1.1.454401.3
		hsw2000c01v1In2Grp1PresTrap NOTIFICATION-TYPE
		OBJECTS { trapCounter, hsw2000c01v1Index, hsw2000c01v1In2Grp1Pres }
		STATUS current
		DESCRIPTION
			"Audio group 1 packet presence Trap"
		::= { hsw2000c01v1Traps 273 }

		-- 1.3.6.1.4.1.10106.2.1.1.454401.3
		hsw2000c01v1In2Grp2PresTrap NOTIFICATION-TYPE
		OBJECTS { trapCounter, hsw2000c01v1Index, hsw2000c01v1In2Grp2Pres }
		STATUS current
		DESCRIPTION
			"Audio group 2 packet presence Trap"
		::= { hsw2000c01v1Traps 275 }

		-- 1.3.6.1.4.1.10106.2.1.1.454401.3
		hsw2000c01v1In2Grp3PresTrap NOTIFICATION-TYPE
		OBJECTS { trapCounter, hsw2000c01v1Index, hsw2000c01v1In2Grp3Pres }
		STATUS current
		DESCRIPTION
			"Audio group 3 packet presence Trap"
		::= { hsw2000c01v1Traps 277 }

		-- 1.3.6.1.4.1.10106.2.1.1.454401.3
		hsw2000c01v1In2Grp4PresTrap NOTIFICATION-TYPE
		OBJECTS { trapCounter, hsw2000c01v1Index, hsw2000c01v1In2Grp4Pres }
		STATUS current
		DESCRIPTION
			"Audio group 4 packet presence Trap"
		::= { hsw2000c01v1Traps 279 }

		-- 1.3.6.1.4.1.10106.2.1.1.454401.3
		hsw2000c01v1In2Grp1P0StatTrap NOTIFICATION-TYPE
		OBJECTS { trapCounter, hsw2000c01v1Index, hsw2000c01v1In2Grp1P0Stat }
		STATUS current
		DESCRIPTION
			"Audio group 1 pair 0 status Trap"
		::= { hsw2000c01v1Traps 281 }

		-- 1.3.6.1.4.1.10106.2.1.1.454401.3
		hsw2000c01v1In2Grp1P1StatTrap NOTIFICATION-TYPE
		OBJECTS { trapCounter, hsw2000c01v1Index, hsw2000c01v1In2Grp1P1Stat }
		STATUS current
		DESCRIPTION
			"Audio group 1 pair 1 status Trap"
		::= { hsw2000c01v1Traps 283 }

		-- 1.3.6.1.4.1.10106.2.1.1.454401.3
		hsw2000c01v1In2Grp2P0StatTrap NOTIFICATION-TYPE
		OBJECTS { trapCounter, hsw2000c01v1Index, hsw2000c01v1In2Grp2P0Stat }
		STATUS current
		DESCRIPTION
			"Audio group 2 pair 0 status Trap"
		::= { hsw2000c01v1Traps 285 }

		-- 1.3.6.1.4.1.10106.2.1.1.454401.3
		hsw2000c01v1In2Grp2P1StatTrap NOTIFICATION-TYPE
		OBJECTS { trapCounter, hsw2000c01v1Index, hsw2000c01v1In2Grp2P1Stat }
		STATUS current
		DESCRIPTION
			"Audio group 2 pair 1status Trap"
		::= { hsw2000c01v1Traps 287 }

		-- 1.3.6.1.4.1.10106.2.1.1.454401.3
		hsw2000c01v1In2Grp3P0StatTrap NOTIFICATION-TYPE
		OBJECTS { trapCounter, hsw2000c01v1Index, hsw2000c01v1In2Grp3P0Stat }
		STATUS current
		DESCRIPTION
			"Audio group 3 pair 0 status Trap"
		::= { hsw2000c01v1Traps 289 }

		-- 1.3.6.1.4.1.10106.2.1.1.454401.3
		hsw2000c01v1In2Grp3P1StatTrap NOTIFICATION-TYPE
		OBJECTS { trapCounter, hsw2000c01v1Index, hsw2000c01v1In2Grp3P1Stat }
		STATUS current
		DESCRIPTION
			"Audio group 3 pair 1 status Trap"
		::= { hsw2000c01v1Traps 291 }

		-- 1.3.6.1.4.1.10106.2.1.1.454401.3
		hsw2000c01v1In2Grp4P0StatTrap NOTIFICATION-TYPE
		OBJECTS { trapCounter, hsw2000c01v1Index, hsw2000c01v1In2Grp4P0Stat }
		STATUS current
		DESCRIPTION
			"Audio group 4 pair 0 status Trap"
		::= { hsw2000c01v1Traps 293 }

		-- 1.3.6.1.4.1.10106.2.1.1.454401.3
		hsw2000c01v1In2Grp4P1StatTrap NOTIFICATION-TYPE
		OBJECTS { trapCounter, hsw2000c01v1Index, hsw2000c01v1In2Grp4P1Stat }
		STATUS current
		DESCRIPTION
			"Audio group 4 pair 1 status Trap"
		::= { hsw2000c01v1Traps 295 }

		-- 1.3.6.1.4.1.10106.2.1.1.454401.3
		hsw2000c01v1In1WssCodTrap NOTIFICATION-TYPE
		OBJECTS { trapCounter, hsw2000c01v1Index, hsw2000c01v1In1WssCod }
		STATUS current
		DESCRIPTION
			"WSS group 1 data  (b3-b0) Trap"
		::= { hsw2000c01v1Traps 297 }

		-- 1.3.6.1.4.1.10106.2.1.1.454401.3
		hsw2000c01v1In1WssStatTrap NOTIFICATION-TYPE
		OBJECTS { trapCounter, hsw2000c01v1Index, hsw2000c01v1In1WssStat }
		STATUS current
		DESCRIPTION
			"WSS information Trap"
		::= { hsw2000c01v1Traps 299 }

		-- 1.3.6.1.4.1.10106.2.1.1.454401.3
		hsw2000c01v1In1ViiAfdCodTrap NOTIFICATION-TYPE
		OBJECTS { trapCounter, hsw2000c01v1Index, hsw2000c01v1In1ViiAfdCod }
		STATUS current
		DESCRIPTION
			"VII AFD code (a3-a0) Trap"
		::= { hsw2000c01v1Traps 301 }

		-- 1.3.6.1.4.1.10106.2.1.1.454401.3
		hsw2000c01v1In1ViiStatTrap NOTIFICATION-TYPE
		OBJECTS { trapCounter, hsw2000c01v1Index, hsw2000c01v1In1ViiStat }
		STATUS current
		DESCRIPTION
			"VII information Trap"
		::= { hsw2000c01v1Traps 303 }

		-- 1.3.6.1.4.1.10106.2.1.1.454401.3
		hsw2000c01v1In12016AfdCodTrap NOTIFICATION-TYPE
		OBJECTS { trapCounter, hsw2000c01v1Index, hsw2000c01v1In12016AfdCod }
		STATUS current
		DESCRIPTION
			"SMPTE 2016 AFD code (a3-a0) Trap"
		::= { hsw2000c01v1Traps 305 }

		-- 1.3.6.1.4.1.10106.2.1.1.454401.3
		hsw2000c01v1In12016StatTrap NOTIFICATION-TYPE
		OBJECTS { trapCounter, hsw2000c01v1Index, hsw2000c01v1In12016Stat }
		STATUS current
		DESCRIPTION
			"SMPTE 2016 information Trap"
		::= { hsw2000c01v1Traps 307 }

		-- 1.3.6.1.4.1.10106.2.1.1.454401.3
		hsw2000c01v1In2WssCodTrap NOTIFICATION-TYPE
		OBJECTS { trapCounter, hsw2000c01v1Index, hsw2000c01v1In2WssCod }
		STATUS current
		DESCRIPTION
			"WSS group 1 data  (b3-b0) Trap"
		::= { hsw2000c01v1Traps 309 }

		-- 1.3.6.1.4.1.10106.2.1.1.454401.3
		hsw2000c01v1In2WssStatTrap NOTIFICATION-TYPE
		OBJECTS { trapCounter, hsw2000c01v1Index, hsw2000c01v1In2WssStat }
		STATUS current
		DESCRIPTION
			"WSS information Trap"
		::= { hsw2000c01v1Traps 311 }

		-- 1.3.6.1.4.1.10106.2.1.1.454401.3
		hsw2000c01v1In2ViiAfdCodTrap NOTIFICATION-TYPE
		OBJECTS { trapCounter, hsw2000c01v1Index, hsw2000c01v1In2ViiAfdCod }
		STATUS current
		DESCRIPTION
			"VII AFD code (a3-a0) Trap"
		::= { hsw2000c01v1Traps 313 }

		-- 1.3.6.1.4.1.10106.2.1.1.454401.3
		hsw2000c01v1In2ViiStatTrap NOTIFICATION-TYPE
		OBJECTS { trapCounter, hsw2000c01v1Index, hsw2000c01v1In2ViiStat }
		STATUS current
		DESCRIPTION
			"VII information Trap"
		::= { hsw2000c01v1Traps 315 }

		-- 1.3.6.1.4.1.10106.2.1.1.454401.3
		hsw2000c01v1In22016CodTrap NOTIFICATION-TYPE
		OBJECTS { trapCounter, hsw2000c01v1Index, hsw2000c01v1In22016Cod }
		STATUS current
		DESCRIPTION
			"SMPTE 2016 AFD code (a3-a0) Trap"
		::= { hsw2000c01v1Traps 317 }

		-- 1.3.6.1.4.1.10106.2.1.1.454401.3
		hsw2000c01v1In22016StatTrap NOTIFICATION-TYPE
		OBJECTS { trapCounter, hsw2000c01v1Index, hsw2000c01v1In22016Stat }
		STATUS current
		DESCRIPTION
			"SMPTE 2016 information Trap"
		::= { hsw2000c01v1Traps 319 }

		-- 1.3.6.1.4.1.10106.2.1.1.454401.3
		hsw2000c01v1In1TxtLinLowTrap NOTIFICATION-TYPE
		OBJECTS { trapCounter, hsw2000c01v1Index, hsw2000c01v1In1TxtLinLow }
		STATUS current
		DESCRIPTION
			"Low level of teletext lines Trap"
		::= { hsw2000c01v1Traps 321 }

		-- 1.3.6.1.4.1.10106.2.1.1.454401.3
		hsw2000c01v1In2TxtLinLowTrap NOTIFICATION-TYPE
		OBJECTS { trapCounter, hsw2000c01v1Index, hsw2000c01v1In2TxtLinLow }
		STATUS current
		DESCRIPTION
			"Low level of teletext lines Trap"
		::= { hsw2000c01v1Traps 325 }

		-- 1.3.6.1.4.1.10106.2.1.1.454501
		htg2000c01v1Traps OBJECT IDENTIFIER ::= { albalaTraps 454501 }

		-- 1.3.6.1.4.1.10106.2.1.1.454501.3
		htg2000c01v1ExpRefFormatTrap NOTIFICATION-TYPE
		OBJECTS { trapCounter, htg2000c01v1Index, htg2000c01v1ExpRefFormat }
		STATUS current
		DESCRIPTION
			"Allows selecting the expected format of the reference Trap"
		::= { htg2000c01v1Traps 9 }

		-- 1.3.6.1.4.1.10106.2.1.1.454501.3
		htg2000c01v1RefInputTrap NOTIFICATION-TYPE
		OBJECTS { trapCounter, htg2000c01v1Index, htg2000c01v1RefInput }
		STATUS current
		DESCRIPTION
			"Allows selecting the reference input Trap"
		::= { htg2000c01v1Traps 11 }

		-- 1.3.6.1.4.1.10106.2.1.1.454501.3
		htg2000c01v1OutFormat1Trap NOTIFICATION-TYPE
		OBJECTS { trapCounter, htg2000c01v1Index, htg2000c01v1OutFormat1 }
		STATUS current
		DESCRIPTION
			"Allows selecting the output format Trap"
		::= { htg2000c01v1Traps 15 }

		-- 1.3.6.1.4.1.10106.2.1.1.454501.3
		htg2000c01v1OutFormat2Trap NOTIFICATION-TYPE
		OBJECTS { trapCounter, htg2000c01v1Index, htg2000c01v1OutFormat2 }
		STATUS current
		DESCRIPTION
			"Allows selecting the output format Trap"
		::= { htg2000c01v1Traps 83 }

		-- 1.3.6.1.4.1.10106.2.1.1.454501.3
		htg2000c01v1OutFormat3Trap NOTIFICATION-TYPE
		OBJECTS { trapCounter, htg2000c01v1Index, htg2000c01v1OutFormat3 }
		STATUS current
		DESCRIPTION
			"Allows selecting the output format Trap"
		::= { htg2000c01v1Traps 151 }

		-- 1.3.6.1.4.1.10106.2.1.1.454501.3
		htg2000c01v1ArefFailTrap NOTIFICATION-TYPE
		OBJECTS { trapCounter, htg2000c01v1Index, htg2000c01v1ArefFail }
		STATUS current
		DESCRIPTION
			"Indicates the absence of analog reference Trap"
		::= { htg2000c01v1Traps 169 }

		-- 1.3.6.1.4.1.10106.2.1.1.454501.3
		htg2000c01v1DrefFailTrap NOTIFICATION-TYPE
		OBJECTS { trapCounter, htg2000c01v1Index, htg2000c01v1DrefFail }
		STATUS current
		DESCRIPTION
			"Indicates the absence of digital reference Trap"
		::= { htg2000c01v1Traps 171 }

		-- 1.3.6.1.4.1.10106.2.1.1.454501.3
		htg2000c01v1IrefFailTrap NOTIFICATION-TYPE
		OBJECTS { trapCounter, htg2000c01v1Index, htg2000c01v1IrefFail }
		STATUS current
		DESCRIPTION
			"Indicates the absence of internal reference Trap"
		::= { htg2000c01v1Traps 173 }

		-- 1.3.6.1.4.1.10106.2.1.1.454501.3
		htg2000c01v1RefIncFailTrap NOTIFICATION-TYPE
		OBJECTS { trapCounter, htg2000c01v1Index, htg2000c01v1RefIncFail }
		STATUS current
		DESCRIPTION
			"Indicates that the format of the received reference is different from expected Trap"
		::= { htg2000c01v1Traps 175 }

		-- 1.3.6.1.4.1.10106.2.1.1.454501.3
		htg2000c01v1RefLockFailTrap NOTIFICATION-TYPE
		OBJECTS { trapCounter, htg2000c01v1Index, htg2000c01v1RefLockFail }
		STATUS current
		DESCRIPTION
			"Indicates that the module is not locked to the reference Trap"
		::= { htg2000c01v1Traps 177 }

		-- 1.3.6.1.4.1.10106.2.1.1.454501.3
		htg2000c01v1DrefCrcFailTrap NOTIFICATION-TYPE
		OBJECTS { trapCounter, htg2000c01v1Index, htg2000c01v1DrefCrcFail }
		STATUS current
		DESCRIPTION
			"Indicates that the digital reference has CRC/EDH errors Trap"
		::= { htg2000c01v1Traps 179 }

		-- 1.3.6.1.4.1.10106.2.1.1.454501.3
		htg2000c01v1ArefFormatTrap NOTIFICATION-TYPE
		OBJECTS { trapCounter, htg2000c01v1Index, htg2000c01v1ArefFormat }
		STATUS current
		DESCRIPTION
			"Indicates the detected format of the analog reference Trap"
		::= { htg2000c01v1Traps 181 }

		-- 1.3.6.1.4.1.10106.2.1.1.454501.3
		htg2000c01v1DrefFormatTrap NOTIFICATION-TYPE
		OBJECTS { trapCounter, htg2000c01v1Index, htg2000c01v1DrefFormat }
		STATUS current
		DESCRIPTION
			"Indicates the detected format of the digital reference Trap"
		::= { htg2000c01v1Traps 183 }

		-- 1.3.6.1.4.1.10106.2.1.1.454502
		htg2000c01v2Traps OBJECT IDENTIFIER ::= { albalaTraps 454502 }

		-- 1.3.6.1.4.1.10106.2.1.1.454502.3
		htg2000c01v2ExpRefFormatTrap NOTIFICATION-TYPE
		OBJECTS { trapCounter, htg2000c01v2Index, htg2000c01v2ExpRefFormat }
		STATUS current
		DESCRIPTION
			"Allows selecting the expected format of the reference Trap"
		::= { htg2000c01v2Traps 9 }

		-- 1.3.6.1.4.1.10106.2.1.1.454502.3
		htg2000c01v2RefInputTrap NOTIFICATION-TYPE
		OBJECTS { trapCounter, htg2000c01v2Index, htg2000c01v2RefInput }
		STATUS current
		DESCRIPTION
			"Allows selecting the reference input Trap"
		::= { htg2000c01v2Traps 11 }

		-- 1.3.6.1.4.1.10106.2.1.1.454502.3
		htg2000c01v2OutFormat1Trap NOTIFICATION-TYPE
		OBJECTS { trapCounter, htg2000c01v2Index, htg2000c01v2OutFormat1 }
		STATUS current
		DESCRIPTION
			"Allows selecting the output format Trap"
		::= { htg2000c01v2Traps 15 }

		-- 1.3.6.1.4.1.10106.2.1.1.454502.3
		htg2000c01v2OutFormat2Trap NOTIFICATION-TYPE
		OBJECTS { trapCounter, htg2000c01v2Index, htg2000c01v2OutFormat2 }
		STATUS current
		DESCRIPTION
			"Allows selecting the output format Trap"
		::= { htg2000c01v2Traps 83 }

		-- 1.3.6.1.4.1.10106.2.1.1.454502.3
		htg2000c01v2OutFormat3Trap NOTIFICATION-TYPE
		OBJECTS { trapCounter, htg2000c01v2Index, htg2000c01v2OutFormat3 }
		STATUS current
		DESCRIPTION
			"Allows selecting the output format Trap"
		::= { htg2000c01v2Traps 151 }

		-- 1.3.6.1.4.1.10106.2.1.1.454502.3
		htg2000c01v2ArefFailTrap NOTIFICATION-TYPE
		OBJECTS { trapCounter, htg2000c01v2Index, htg2000c01v2ArefFail }
		STATUS current
		DESCRIPTION
			"Indicates the absence of analog reference Trap"
		::= { htg2000c01v2Traps 203 }

		-- 1.3.6.1.4.1.10106.2.1.1.454502.3
		htg2000c01v2DrefFailTrap NOTIFICATION-TYPE
		OBJECTS { trapCounter, htg2000c01v2Index, htg2000c01v2DrefFail }
		STATUS current
		DESCRIPTION
			"Indicates the absence of digital reference Trap"
		::= { htg2000c01v2Traps 205 }

		-- 1.3.6.1.4.1.10106.2.1.1.454502.3
		htg2000c01v2IrefFailTrap NOTIFICATION-TYPE
		OBJECTS { trapCounter, htg2000c01v2Index, htg2000c01v2IrefFail }
		STATUS current
		DESCRIPTION
			"Indicates the absence of internal reference Trap"
		::= { htg2000c01v2Traps 207 }

		-- 1.3.6.1.4.1.10106.2.1.1.454502.3
		htg2000c01v2RefIncFailTrap NOTIFICATION-TYPE
		OBJECTS { trapCounter, htg2000c01v2Index, htg2000c01v2RefIncFail }
		STATUS current
		DESCRIPTION
			"Indicates that the format of the received reference is different from expected Trap"
		::= { htg2000c01v2Traps 209 }

		-- 1.3.6.1.4.1.10106.2.1.1.454502.3
		htg2000c01v2RefLockFailTrap NOTIFICATION-TYPE
		OBJECTS { trapCounter, htg2000c01v2Index, htg2000c01v2RefLockFail }
		STATUS current
		DESCRIPTION
			"Indicates that the module is not locked to the reference Trap"
		::= { htg2000c01v2Traps 211 }

		-- 1.3.6.1.4.1.10106.2.1.1.454502.3
		htg2000c01v2DrefCrcFailTrap NOTIFICATION-TYPE
		OBJECTS { trapCounter, htg2000c01v2Index, htg2000c01v2DrefCrcFail }
		STATUS current
		DESCRIPTION
			"Indicates that the digital reference has CRC/EDH errors Trap"
		::= { htg2000c01v2Traps 213 }

		-- 1.3.6.1.4.1.10106.2.1.1.454502.3
		htg2000c01v2ArefFormatTrap NOTIFICATION-TYPE
		OBJECTS { trapCounter, htg2000c01v2Index, htg2000c01v2ArefFormat }
		STATUS current
		DESCRIPTION
			"Indicates the detected format of the analog reference Trap"
		::= { htg2000c01v2Traps 217 }

		-- 1.3.6.1.4.1.10106.2.1.1.454502.3
		htg2000c01v2DrefFormatTrap NOTIFICATION-TYPE
		OBJECTS { trapCounter, htg2000c01v2Index, htg2000c01v2DrefFormat }
		STATUS current
		DESCRIPTION
			"Indicates the detected format of the digital reference Trap"
		::= { htg2000c01v2Traps 219 }

		-- 1.3.6.1.4.1.10106.2.1.1.456201
		aad2000c01v1Traps OBJECT IDENTIFIER ::= { albalaTraps 456201 }

		-- 1.3.6.1.4.1.10106.2.1.1.456201.3
		aad2000c01v1SilenceTrap NOTIFICATION-TYPE
		OBJECTS { trapCounter, aad2000c01v1Index, aad2000c01v1Silence }
		STATUS current
		DESCRIPTION
			"Silence fail Trap"
		::= { aad2000c01v1Traps 17 }

		-- 1.3.6.1.4.1.10106.2.1.1.456201.3
		aad2000c01v1OverloadTrap NOTIFICATION-TYPE
		OBJECTS { trapCounter, aad2000c01v1Index, aad2000c01v1Overload }
		STATUS current
		DESCRIPTION
			"Overload fail Trap"
		::= { aad2000c01v1Traps 19 }

		-- 1.3.6.1.4.1.10106.2.1.1.460201
		aad2000c02v1Traps OBJECT IDENTIFIER ::= { albalaTraps 460201 }

		-- 1.3.6.1.4.1.10106.2.1.1.460201.3
		aad2000c02v1SilenceTrap NOTIFICATION-TYPE
		OBJECTS { trapCounter, aad2000c02v1Index, aad2000c02v1Silence }
		STATUS current
		DESCRIPTION
			"Silence fail Trap"
		::= { aad2000c02v1Traps 17 }

		-- 1.3.6.1.4.1.10106.2.1.1.460201.3
		aad2000c02v1OverloadTrap NOTIFICATION-TYPE
		OBJECTS { trapCounter, aad2000c02v1Index, aad2000c02v1Overload }
		STATUS current
		DESCRIPTION
			"Overload fail Trap"
		::= { aad2000c02v1Traps 19 }

		-- 1.3.6.1.4.1.10106.2.1.1.460301
		aad2000c03v1Traps OBJECT IDENTIFIER ::= { albalaTraps 460301 }

		-- 1.3.6.1.4.1.10106.2.1.1.460301.3
		aad2000c03v1SilenceTrap NOTIFICATION-TYPE
		OBJECTS { trapCounter, aad2000c03v1Index, aad2000c03v1Silence }
		STATUS current
		DESCRIPTION
			"Silence fail Trap"
		::= { aad2000c03v1Traps 17 }

		-- 1.3.6.1.4.1.10106.2.1.1.460301.3
		aad2000c03v1OverloadTrap NOTIFICATION-TYPE
		OBJECTS { trapCounter, aad2000c03v1Index, aad2000c03v1Overload }
		STATUS current
		DESCRIPTION
			"Overload fail Trap"
		::= { aad2000c03v1Traps 19 }

		-- 1.3.6.1.4.1.10106.2.1.1.460401
		aad2000c04v1Traps OBJECT IDENTIFIER ::= { albalaTraps 460401 }

		-- 1.3.6.1.4.1.10106.2.1.1.460401.3
		aad2000c04v1SilenceTrap NOTIFICATION-TYPE
		OBJECTS { trapCounter, aad2000c04v1Index, aad2000c04v1Silence }
		STATUS current
		DESCRIPTION
			"Silence fail Trap"
		::= { aad2000c04v1Traps 17 }

		-- 1.3.6.1.4.1.10106.2.1.1.460401.3
		aad2000c04v1OverloadTrap NOTIFICATION-TYPE
		OBJECTS { trapCounter, aad2000c04v1Index, aad2000c04v1Overload }
		STATUS current
		DESCRIPTION
			"Overload fail Trap"
		::= { aad2000c04v1Traps 19 }

		-- 1.3.6.1.4.1.10106.2.1.1.461001
		ipa2000c01v1Traps OBJECT IDENTIFIER ::= { albalaTraps 461001 }

		-- 1.3.6.1.4.1.10106.2.1.1.461001.3
		ipa2000c01v1InputTrap NOTIFICATION-TYPE
		OBJECTS { trapCounter, ipa2000c01v1Index, ipa2000c01v1Input }
		STATUS current
		DESCRIPTION
			"Selected input Trap"
		::= { ipa2000c01v1Traps 19 }

		-- 1.3.6.1.4.1.10106.2.1.1.461001.3
		ipa2000c01v1SwModeTrap NOTIFICATION-TYPE
		OBJECTS { trapCounter, ipa2000c01v1Index, ipa2000c01v1SwMode }
		STATUS current
		DESCRIPTION
			"Allows selecting the switching mode Trap"
		::= { ipa2000c01v1Traps 21 }

		-- 1.3.6.1.4.1.10106.2.1.1.461001.3
		ipa2000c01v1Ch1PriorTrap NOTIFICATION-TYPE
		OBJECTS { trapCounter, ipa2000c01v1Index, ipa2000c01v1Ch1Prior }
		STATUS current
		DESCRIPTION
			"Allows selecting channel input priority Trap"
		::= { ipa2000c01v1Traps 23 }

		-- 1.3.6.1.4.1.10106.2.1.1.461001.3
		ipa2000c01v1Ch2PriorTrap NOTIFICATION-TYPE
		OBJECTS { trapCounter, ipa2000c01v1Index, ipa2000c01v1Ch2Prior }
		STATUS current
		DESCRIPTION
			"Allows selecting channel input priority Trap"
		::= { ipa2000c01v1Traps 25 }

		-- 1.3.6.1.4.1.10106.2.1.1.461001.3
		ipa2000c01v1DvbTModeTrap NOTIFICATION-TYPE
		OBJECTS { trapCounter, ipa2000c01v1Index, ipa2000c01v1DvbTMode }
		STATUS current
		DESCRIPTION
			"Selects DVB-T mode. Trap"
		::= { ipa2000c01v1Traps 33 }

		-- 1.3.6.1.4.1.10106.2.1.1.461001.3
		ipa2000c01v1Ch1SelectionTrap NOTIFICATION-TYPE
		OBJECTS { trapCounter, ipa2000c01v1Index, ipa2000c01v1Ch1Selection }
		STATUS current
		DESCRIPTION
			"Input selection Trap"
		::= { ipa2000c01v1Traps 61 }

		-- 1.3.6.1.4.1.10106.2.1.1.461001.3
		ipa2000c01v1Ch2SelectionTrap NOTIFICATION-TYPE
		OBJECTS { trapCounter, ipa2000c01v1Index, ipa2000c01v1Ch2Selection }
		STATUS current
		DESCRIPTION
			"Input selection Trap"
		::= { ipa2000c01v1Traps 63 }

		-- 1.3.6.1.4.1.10106.2.1.1.461001.3
		ipa2000c01v1OutDelayTrap NOTIFICATION-TYPE
		OBJECTS { trapCounter, ipa2000c01v1Index, ipa2000c01v1OutDelay }
		STATUS current
		DESCRIPTION
			"Output delay refered to 1PPS reference in DVB-T mode Trap"
		::= { ipa2000c01v1Traps 79 }

		-- 1.3.6.1.4.1.10106.2.1.1.461001.3
		ipa2000c01v1PacketDelayTrap NOTIFICATION-TYPE
		OBJECTS { trapCounter, ipa2000c01v1Index, ipa2000c01v1PacketDelay }
		STATUS current
		DESCRIPTION
			"Output delay in TS packets in non DVB-T mode Trap"
		::= { ipa2000c01v1Traps 81 }

		-- 1.3.6.1.4.1.10106.2.1.1.461001.3
		ipa2000c01v1Link1Trap NOTIFICATION-TYPE
		OBJECTS { trapCounter, ipa2000c01v1Index, ipa2000c01v1Link1 }
		STATUS current
		DESCRIPTION
			"Ethernet conection status Trap"
		::= { ipa2000c01v1Traps 377 }

		-- 1.3.6.1.4.1.10106.2.1.1.461001.3
		ipa2000c01v1System1Trap NOTIFICATION-TYPE
		OBJECTS { trapCounter, ipa2000c01v1Index, ipa2000c01v1System1 }
		STATUS current
		DESCRIPTION
			"Ethernet conection system Trap"
		::= { ipa2000c01v1Traps 379 }

		-- 1.3.6.1.4.1.10106.2.1.1.461001.3
		ipa2000c01v1Link2Trap NOTIFICATION-TYPE
		OBJECTS { trapCounter, ipa2000c01v1Index, ipa2000c01v1Link2 }
		STATUS current
		DESCRIPTION
			"Ethernet conection status Trap"
		::= { ipa2000c01v1Traps 381 }

		-- 1.3.6.1.4.1.10106.2.1.1.461001.3
		ipa2000c01v1System2Trap NOTIFICATION-TYPE
		OBJECTS { trapCounter, ipa2000c01v1Index, ipa2000c01v1System2 }
		STATUS current
		DESCRIPTION
			"Ethernet conection system Trap"
		::= { ipa2000c01v1Traps 383 }

		-- 1.3.6.1.4.1.10106.2.1.1.461001.3
		ipa2000c01v11ppsFailTrap NOTIFICATION-TYPE
		OBJECTS { trapCounter, ipa2000c01v1Index, ipa2000c01v11ppsFail }
		STATUS current
		DESCRIPTION
			"1PPS reference input status Trap"
		::= { ipa2000c01v1Traps 385 }

		-- 1.3.6.1.4.1.10106.2.1.1.461001.3
		ipa2000c01v113mhzFailTrap NOTIFICATION-TYPE
		OBJECTS { trapCounter, ipa2000c01v1Index, ipa2000c01v113mhzFail }
		STATUS current
		DESCRIPTION
			"13.5 MHz internal backplane reference input status Trap"
		::= { ipa2000c01v1Traps 387 }

		-- 1.3.6.1.4.1.10106.2.1.1.461001.3
		ipa2000c01v1OutputFailTrap NOTIFICATION-TYPE
		OBJECTS { trapCounter, ipa2000c01v1Index, ipa2000c01v1OutputFail }
		STATUS current
		DESCRIPTION
			"The output signal is not valid because all inputs failed Trap"
		::= { ipa2000c01v1Traps 389 }

		-- 1.3.6.1.4.1.10106.2.1.1.461001.3
		ipa2000c01v1SyncLossErr1Trap NOTIFICATION-TYPE
		OBJECTS { trapCounter, ipa2000c01v1Index, ipa2000c01v1SyncLossErr1 }
		STATUS current
		DESCRIPTION
			"Sync loss fail (Fist priority  parameter 1.1) Trap"
		::= { ipa2000c01v1Traps 395 }

		-- 1.3.6.1.4.1.10106.2.1.1.461001.3
		ipa2000c01v1SyncByteErr1Trap NOTIFICATION-TYPE
		OBJECTS { trapCounter, ipa2000c01v1Index, ipa2000c01v1SyncByteErr1 }
		STATUS current
		DESCRIPTION
			"Sync byte error (Fist priority  parameter 1.2) Trap"
		::= { ipa2000c01v1Traps 397 }

		-- 1.3.6.1.4.1.10106.2.1.1.461001.3
		ipa2000c01v1PatError1Trap NOTIFICATION-TYPE
		OBJECTS { trapCounter, ipa2000c01v1Index, ipa2000c01v1PatError1 }
		STATUS current
		DESCRIPTION
			"PAT error (Fist priority  parameter 1.3) Trap"
		::= { ipa2000c01v1Traps 399 }

		-- 1.3.6.1.4.1.10106.2.1.1.461001.3
		ipa2000c01v1CcError1Trap NOTIFICATION-TYPE
		OBJECTS { trapCounter, ipa2000c01v1Index, ipa2000c01v1CcError1 }
		STATUS current
		DESCRIPTION
			"Continuity counter error (Fist priority  parameter 1.4) Trap"
		::= { ipa2000c01v1Traps 401 }

		-- 1.3.6.1.4.1.10106.2.1.1.461001.3
		ipa2000c01v1PmtError1Trap NOTIFICATION-TYPE
		OBJECTS { trapCounter, ipa2000c01v1Index, ipa2000c01v1PmtError1 }
		STATUS current
		DESCRIPTION
			"PMT error (Fist priority  parameter 1.5) Trap"
		::= { ipa2000c01v1Traps 403 }

		-- 1.3.6.1.4.1.10106.2.1.1.461001.3
		ipa2000c01v1PidError1Trap NOTIFICATION-TYPE
		OBJECTS { trapCounter, ipa2000c01v1Index, ipa2000c01v1PidError1 }
		STATUS current
		DESCRIPTION
			"PID error (Fist priority  parameter 1.6) Trap"
		::= { ipa2000c01v1Traps 405 }

		-- 1.3.6.1.4.1.10106.2.1.1.461001.3
		ipa2000c01v1MipError1Trap NOTIFICATION-TYPE
		OBJECTS { trapCounter, ipa2000c01v1Index, ipa2000c01v1MipError1 }
		STATUS current
		DESCRIPTION
			"MIP error. DVB-T compliant Trap"
		::= { ipa2000c01v1Traps 407 }

		-- 1.3.6.1.4.1.10106.2.1.1.461001.3
		ipa2000c01v1GlobalError1Trap NOTIFICATION-TYPE
		OBJECTS { trapCounter, ipa2000c01v1Index, ipa2000c01v1GlobalError1 }
		STATUS current
		DESCRIPTION
			"Global fail Trap"
		::= { ipa2000c01v1Traps 409 }

		-- 1.3.6.1.4.1.10106.2.1.1.461001.3
		ipa2000c01v1SyncLossErr2Trap NOTIFICATION-TYPE
		OBJECTS { trapCounter, ipa2000c01v1Index, ipa2000c01v1SyncLossErr2 }
		STATUS current
		DESCRIPTION
			"Sync loss fail (Fist priority  parameter 1.1) Trap"
		::= { ipa2000c01v1Traps 411 }

		-- 1.3.6.1.4.1.10106.2.1.1.461001.3
		ipa2000c01v1SyncByteErr2Trap NOTIFICATION-TYPE
		OBJECTS { trapCounter, ipa2000c01v1Index, ipa2000c01v1SyncByteErr2 }
		STATUS current
		DESCRIPTION
			"Sync byte error (Fist priority  parameter 1.2) Trap"
		::= { ipa2000c01v1Traps 413 }

		-- 1.3.6.1.4.1.10106.2.1.1.461001.3
		ipa2000c01v1PatError2Trap NOTIFICATION-TYPE
		OBJECTS { trapCounter, ipa2000c01v1Index, ipa2000c01v1PatError2 }
		STATUS current
		DESCRIPTION
			"PAT error (Fist priority  parameter 1.3) Trap"
		::= { ipa2000c01v1Traps 415 }

		-- 1.3.6.1.4.1.10106.2.1.1.461001.3
		ipa2000c01v1CcError2Trap NOTIFICATION-TYPE
		OBJECTS { trapCounter, ipa2000c01v1Index, ipa2000c01v1CcError2 }
		STATUS current
		DESCRIPTION
			"Continuity counter error (Fist priority  parameter 1.4) Trap"
		::= { ipa2000c01v1Traps 417 }

		-- 1.3.6.1.4.1.10106.2.1.1.461001.3
		ipa2000c01v1PmtError2Trap NOTIFICATION-TYPE
		OBJECTS { trapCounter, ipa2000c01v1Index, ipa2000c01v1PmtError2 }
		STATUS current
		DESCRIPTION
			"PMT error (Fist priority  parameter 1.5) Trap"
		::= { ipa2000c01v1Traps 419 }

		-- 1.3.6.1.4.1.10106.2.1.1.461001.3
		ipa2000c01v1PidError2Trap NOTIFICATION-TYPE
		OBJECTS { trapCounter, ipa2000c01v1Index, ipa2000c01v1PidError2 }
		STATUS current
		DESCRIPTION
			"PID error (Fist priority  parameter 1.6) Trap"
		::= { ipa2000c01v1Traps 421 }

		-- 1.3.6.1.4.1.10106.2.1.1.461001.3
		ipa2000c01v1MipError2Trap NOTIFICATION-TYPE
		OBJECTS { trapCounter, ipa2000c01v1Index, ipa2000c01v1MipError2 }
		STATUS current
		DESCRIPTION
			"MIP error. DVB-T compliant Trap"
		::= { ipa2000c01v1Traps 423 }

		-- 1.3.6.1.4.1.10106.2.1.1.461001.3
		ipa2000c01v1GlobalError2Trap NOTIFICATION-TYPE
		OBJECTS { trapCounter, ipa2000c01v1Index, ipa2000c01v1GlobalError2 }
		STATUS current
		DESCRIPTION
			"Global fail Trap"
		::= { ipa2000c01v1Traps 425 }

		-- 1.3.6.1.4.1.10106.2.1.1.461001.3
		ipa2000c01v1Ch1DelWarTrap NOTIFICATION-TYPE
		OBJECTS { trapCounter, ipa2000c01v1Index, ipa2000c01v1Ch1DelWar }
		STATUS current
		DESCRIPTION
			"The delay is greater than the programmed output delay Trap"
		::= { ipa2000c01v1Traps 427 }

		-- 1.3.6.1.4.1.10106.2.1.1.461001.3
		ipa2000c01v1Ch2DelWarTrap NOTIFICATION-TYPE
		OBJECTS { trapCounter, ipa2000c01v1Index, ipa2000c01v1Ch2DelWar }
		STATUS current
		DESCRIPTION
			"The channel 2 delay is greater than the programmed output delay Trap"
		::= { ipa2000c01v1Traps 429 }

		-- 1.3.6.1.4.1.10106.2.1.1.461001.3
		ipa2000c01v1GlobalSeamTrap NOTIFICATION-TYPE
		OBJECTS { trapCounter, ipa2000c01v1Index, ipa2000c01v1GlobalSeam }
		STATUS current
		DESCRIPTION
			"Global seamles switching capability Trap"
		::= { ipa2000c01v1Traps 431 }

		-- 1.3.6.1.4.1.10106.2.1.1.467901
		tle2001c02v1Traps OBJECT IDENTIFIER ::= { albalaTraps 467901 }

		-- 1.3.6.1.4.1.10106.2.1.1.467901.3
		tle2001c02v1Gpi1Trap NOTIFICATION-TYPE
		OBJECTS { trapCounter, tle2001c02v1Index, tle2001c02v1Gpi1 }
		STATUS current
		DESCRIPTION
			"GPI1 status Trap"
		::= { tle2001c02v1Traps 27 }

		-- 1.3.6.1.4.1.10106.2.1.1.467901.3
		tle2001c02v1Gpi2Trap NOTIFICATION-TYPE
		OBJECTS { trapCounter, tle2001c02v1Index, tle2001c02v1Gpi2 }
		STATUS current
		DESCRIPTION
			"GPI2 status Trap"
		::= { tle2001c02v1Traps 29 }

		-- 1.3.6.1.4.1.10106.2.1.1.467901.3
		tle2001c02v1Gpi3Trap NOTIFICATION-TYPE
		OBJECTS { trapCounter, tle2001c02v1Index, tle2001c02v1Gpi3 }
		STATUS current
		DESCRIPTION
			"GPI3 status Trap"
		::= { tle2001c02v1Traps 31 }

		-- 1.3.6.1.4.1.10106.2.1.1.467901.3
		tle2001c02v1Gpi4Trap NOTIFICATION-TYPE
		OBJECTS { trapCounter, tle2001c02v1Index, tle2001c02v1Gpi4 }
		STATUS current
		DESCRIPTION
			"GPI4 status Trap"
		::= { tle2001c02v1Traps 33 }

		-- 1.3.6.1.4.1.10106.2.1.1.467901.3
		tle2001c02v1RedBoardTrap NOTIFICATION-TYPE
		OBJECTS { trapCounter, tle2001c02v1Index, tle2001c02v1RedBoard }
		STATUS current
		DESCRIPTION
			"Indicates that there are two modules in redundant configuration Trap"
		::= { tle2001c02v1Traps 35 }

		-- 1.3.6.1.4.1.10106.2.1.1.467901.3
		tle2001c02v1EthLinkTrap NOTIFICATION-TYPE
		OBJECTS { trapCounter, tle2001c02v1Index, tle2001c02v1EthLink }
		STATUS current
		DESCRIPTION
			"Indicates that the Ethernet link is OK Trap"
		::= { tle2001c02v1Traps 37 }

		-- 1.3.6.1.4.1.10106.2.1.1.467901.3
		tle2001c02v1EthRedActTrap NOTIFICATION-TYPE
		OBJECTS { trapCounter, tle2001c02v1Index, tle2001c02v1EthRedAct }
		STATUS current
		DESCRIPTION
			"Indicates that this is the active module of the redundant configuration Trap"
		::= { tle2001c02v1Traps 39 }

		-- 1.3.6.1.4.1.10106.2.1.1.469001
		ddf2008c01v1Traps OBJECT IDENTIFIER ::= { albalaTraps 469001 }

		-- 1.3.6.1.4.1.10106.2.1.1.469001.3
		ddf2008c01v1BackplaneLockedTrap NOTIFICATION-TYPE
		OBJECTS { trapCounter, ddf2008c01v1Index, ddf2008c01v1BackplaneLocked }
		STATUS current
		DESCRIPTION
			"Locked to internal bus audio (MCLK and WCLK valid and locked) Trap"
		::= { ddf2008c01v1Traps 141 }

		-- 1.3.6.1.4.1.10106.2.1.1.470001
		hfs2000c01v1Traps OBJECT IDENTIFIER ::= { albalaTraps 470001 }

		-- 1.3.6.1.4.1.10106.2.1.1.470001.3
		hfs2000c01v1NoSigTrap NOTIFICATION-TYPE
		OBJECTS { trapCounter, hfs2000c01v1Index, hfs2000c01v1NoSig }
		STATUS current
		DESCRIPTION
			"Indicates SDI signal fail Trap"
		::= { hfs2000c01v1Traps 89 }

		-- 1.3.6.1.4.1.10106.2.1.1.470001.3
		hfs2000c01v1UnlockTrap NOTIFICATION-TYPE
		OBJECTS { trapCounter, hfs2000c01v1Index, hfs2000c01v1Unlock }
		STATUS current
		DESCRIPTION
			"Indicates signal unlock Trap"
		::= { hfs2000c01v1Traps 91 }

		-- 1.3.6.1.4.1.10106.2.1.1.470001.3
		hfs2000c01v1EdhCrcTrap NOTIFICATION-TYPE
		OBJECTS { trapCounter, hfs2000c01v1Index, hfs2000c01v1EdhCrc }
		STATUS current
		DESCRIPTION
			"Indicates presence of EDH/CRC errors Trap"
		::= { hfs2000c01v1Traps 93 }

		-- 1.3.6.1.4.1.10106.2.1.1.470001.3
		hfs2000c01v1NoRefTrap NOTIFICATION-TYPE
		OBJECTS { trapCounter, hfs2000c01v1Index, hfs2000c01v1NoRef }
		STATUS current
		DESCRIPTION
			"Indicates reference signal fail Trap"
		::= { hfs2000c01v1Traps 95 }

		-- 1.3.6.1.4.1.10106.2.1.1.470001.3
		hfs2000c01v1RefUnlockTrap NOTIFICATION-TYPE
		OBJECTS { trapCounter, hfs2000c01v1Index, hfs2000c01v1RefUnlock }
		STATUS current
		DESCRIPTION
			"Indicates reference signal unlock fail Trap"
		::= { hfs2000c01v1Traps 97 }

		-- 1.3.6.1.4.1.10106.2.1.1.471001
		htc3000c01v1Traps OBJECT IDENTIFIER ::= { albalaTraps 471001 }

		-- 1.3.6.1.4.1.10106.2.1.1.471001.3
		htc3000c01v1RefAbsentTrap NOTIFICATION-TYPE
		OBJECTS { trapCounter, htc3000c01v1Index, htc3000c01v1RefAbsent }
		STATUS current
		DESCRIPTION
			"There is no reference signal Trap"
		::= { htc3000c01v1Traps 93 }

		-- 1.3.6.1.4.1.10106.2.1.1.471001.3
		htc3000c01v1RefUnlockTrap NOTIFICATION-TYPE
		OBJECTS { trapCounter, htc3000c01v1Index, htc3000c01v1RefUnlock }
		STATUS current
		DESCRIPTION
			"Reference input unlock fail Trap"
		::= { htc3000c01v1Traps 95 }

		-- 1.3.6.1.4.1.10106.2.1.1.471001.3
		htc3000c01v1NoSignalMainTrap NOTIFICATION-TYPE
		OBJECTS { trapCounter, htc3000c01v1Index, htc3000c01v1NoSignalMain }
		STATUS current
		DESCRIPTION
			"There is no SDI signal or the format is not supported in PGM IN Trap"
		::= { htc3000c01v1Traps 97 }

		-- 1.3.6.1.4.1.10106.2.1.1.471001.3
		htc3000c01v1UnlockMainTrap NOTIFICATION-TYPE
		OBJECTS { trapCounter, htc3000c01v1Index, htc3000c01v1UnlockMain }
		STATUS current
		DESCRIPTION
			"It indicates signal unlock fail Trap"
		::= { htc3000c01v1Traps 99 }

		-- 1.3.6.1.4.1.10106.2.1.1.471001.3
		htc3000c01v1EdhErrorMainTrap NOTIFICATION-TYPE
		OBJECTS { trapCounter, htc3000c01v1Index, htc3000c01v1EdhErrorMain }
		STATUS current
		DESCRIPTION
			"There are EDH/CRC errors on PGM IN Trap"
		::= { htc3000c01v1Traps 101 }

		-- 1.3.6.1.4.1.10106.2.1.1.471001.3
		htc3000c01v1NoSignalAuxTrap NOTIFICATION-TYPE
		OBJECTS { trapCounter, htc3000c01v1Index, htc3000c01v1NoSignalAux }
		STATUS current
		DESCRIPTION
			"There is no SDI signal or the format is not supported in AUX IN Trap"
		::= { htc3000c01v1Traps 103 }

		-- 1.3.6.1.4.1.10106.2.1.1.471001.3
		htc3000c01v1UnlockAuxTrap NOTIFICATION-TYPE
		OBJECTS { trapCounter, htc3000c01v1Index, htc3000c01v1UnlockAux }
		STATUS current
		DESCRIPTION
			"It indicates signal AUX IN unlock fail Trap"
		::= { htc3000c01v1Traps 105 }

		-- 1.3.6.1.4.1.10106.2.1.1.471001.3
		htc3000c01v1EdhErrorAuxTrap NOTIFICATION-TYPE
		OBJECTS { trapCounter, htc3000c01v1Index, htc3000c01v1EdhErrorAux }
		STATUS current
		DESCRIPTION
			"There are EDH/CRC errors on AUX IN signal Trap"
		::= { htc3000c01v1Traps 107 }

		-- 1.3.6.1.4.1.10106.2.1.1.471001.3
		htc3000c01v1IncompFmtTrap NOTIFICATION-TYPE
		OBJECTS { trapCounter, htc3000c01v1Index, htc3000c01v1IncompFmt }
		STATUS current
		DESCRIPTION
			"It indicates if there are incompatible formats (european-american) Trap"
		::= { htc3000c01v1Traps 109 }

		-- 1.3.6.1.4.1.10106.2.1.1.471001.3
		htc3000c01v1TcFailTrap NOTIFICATION-TYPE
		OBJECTS { trapCounter, htc3000c01v1Index, htc3000c01v1TcFail }
		STATUS current
		DESCRIPTION
			"It indicates if there is a reception Time Code fail Trap"
		::= { htc3000c01v1Traps 111 }

		-- 1.3.6.1.4.1.10106.2.1.1.473501
		tle3001c02v1Traps OBJECT IDENTIFIER ::= { albalaTraps 473501 }

		-- 1.3.6.1.4.1.10106.2.1.1.473501.3
		tle3001c02v1Gpi1Trap NOTIFICATION-TYPE
		OBJECTS { trapCounter, tle3001c02v1Index, tle3001c02v1Gpi1 }
		STATUS current
		DESCRIPTION
			"GPI1 status Trap"
		::= { tle3001c02v1Traps 31 }

		-- 1.3.6.1.4.1.10106.2.1.1.473501.3
		tle3001c02v1Gpi2Trap NOTIFICATION-TYPE
		OBJECTS { trapCounter, tle3001c02v1Index, tle3001c02v1Gpi2 }
		STATUS current
		DESCRIPTION
			"GPI2 status Trap"
		::= { tle3001c02v1Traps 33 }

		-- 1.3.6.1.4.1.10106.2.1.1.473501.3
		tle3001c02v1Gpi3Trap NOTIFICATION-TYPE
		OBJECTS { trapCounter, tle3001c02v1Index, tle3001c02v1Gpi3 }
		STATUS current
		DESCRIPTION
			"GPI3 status Trap"
		::= { tle3001c02v1Traps 35 }

		-- 1.3.6.1.4.1.10106.2.1.1.473501.3
		tle3001c02v1Gpi4Trap NOTIFICATION-TYPE
		OBJECTS { trapCounter, tle3001c02v1Index, tle3001c02v1Gpi4 }
		STATUS current
		DESCRIPTION
			"GPI4 status Trap"
		::= { tle3001c02v1Traps 37 }

		-- 1.3.6.1.4.1.10106.2.1.1.473501.3
		tle3001c02v1RedBoardTrap NOTIFICATION-TYPE
		OBJECTS { trapCounter, tle3001c02v1Index, tle3001c02v1RedBoard }
		STATUS current
		DESCRIPTION
			"Indicates that there are two modules in redundant configuration Trap"
		::= { tle3001c02v1Traps 39 }

		-- 1.3.6.1.4.1.10106.2.1.1.473501.3
		tle3001c02v1EthLinkTrap NOTIFICATION-TYPE
		OBJECTS { trapCounter, tle3001c02v1Index, tle3001c02v1EthLink }
		STATUS current
		DESCRIPTION
			"Indicates that the Ethernet link is OK Trap"
		::= { tle3001c02v1Traps 41 }

		-- 1.3.6.1.4.1.10106.2.1.1.473501.3
		tle3001c02v1EthRedActTrap NOTIFICATION-TYPE
		OBJECTS { trapCounter, tle3001c02v1Index, tle3001c02v1EthRedAct }
		STATUS current
		DESCRIPTION
			"Indicates that this is the active module of the redundant configuration Trap"
		::= { tle3001c02v1Traps 43 }

		-- 1.3.6.1.4.1.10106.2.1.1.474701
		adf2008c01v1Traps OBJECT IDENTIFIER ::= { albalaTraps 474701 }

		-- 1.3.6.1.4.1.10106.2.1.1.474701.3
		adf2008c01v1BackplaneLockedTrap NOTIFICATION-TYPE
		OBJECTS { trapCounter, adf2008c01v1Index, adf2008c01v1BackplaneLocked }
		STATUS current
		DESCRIPTION
			"Locked to internal bus audio (MCLK and WCLK valid and locked) Trap"
		::= { adf2008c01v1Traps 105 }

		-- 1.3.6.1.4.1.10106.2.1.1.474701.3
		adf2008c01v1AnalogInOverflTrap NOTIFICATION-TYPE
		OBJECTS { trapCounter, adf2008c01v1Index, adf2008c01v1AnalogInOverfl }
		STATUS current
		DESCRIPTION
			"Analog inputs overflow Trap"
		::= { adf2008c01v1Traps 171 }

		-- 1.3.6.1.4.1.10106.2.1.1.474801
		daf2008c01v1Traps OBJECT IDENTIFIER ::= { albalaTraps 474801 }

		-- 1.3.6.1.4.1.10106.2.1.1.474801.3
		daf2008c01v1BackplaneLockedTrap NOTIFICATION-TYPE
		OBJECTS { trapCounter, daf2008c01v1Index, daf2008c01v1BackplaneLocked }
		STATUS current
		DESCRIPTION
			"Locked to internal bus audio (MCLK and WCLK valid and locked) Trap"
		::= { daf2008c01v1Traps 59 }

		-- 1.3.6.1.4.1.10106.2.1.1.478401
		tly3032c04v1Traps OBJECT IDENTIFIER ::= { albalaTraps 478401 }

		-- 1.3.6.1.4.1.10106.2.1.1.478401.3
		tly3032c04v1Gpi1Trap NOTIFICATION-TYPE
		OBJECTS { trapCounter, tly3032c04v1Index, tly3032c04v1Gpi1 }
		STATUS current
		DESCRIPTION
			"GPI1 status Trap"
		::= { tly3032c04v1Traps 3 }

		-- 1.3.6.1.4.1.10106.2.1.1.478401.3
		tly3032c04v1Gpi2Trap NOTIFICATION-TYPE
		OBJECTS { trapCounter, tly3032c04v1Index, tly3032c04v1Gpi2 }
		STATUS current
		DESCRIPTION
			"GPI2 status Trap"
		::= { tly3032c04v1Traps 5 }

		-- 1.3.6.1.4.1.10106.2.1.1.478401.3
		tly3032c04v1Gpi3Trap NOTIFICATION-TYPE
		OBJECTS { trapCounter, tly3032c04v1Index, tly3032c04v1Gpi3 }
		STATUS current
		DESCRIPTION
			"GPI3 status Trap"
		::= { tly3032c04v1Traps 7 }

		-- 1.3.6.1.4.1.10106.2.1.1.478401.3
		tly3032c04v1Gpi4Trap NOTIFICATION-TYPE
		OBJECTS { trapCounter, tly3032c04v1Index, tly3032c04v1Gpi4 }
		STATUS current
		DESCRIPTION
			"GPI4 status Trap"
		::= { tly3032c04v1Traps 9 }

		-- 1.3.6.1.4.1.10106.2.1.1.478401.3
		tly3032c04v1Gpi5Trap NOTIFICATION-TYPE
		OBJECTS { trapCounter, tly3032c04v1Index, tly3032c04v1Gpi5 }
		STATUS current
		DESCRIPTION
			"GPI5 status Trap"
		::= { tly3032c04v1Traps 11 }

		-- 1.3.6.1.4.1.10106.2.1.1.478401.3
		tly3032c04v1Gpi6Trap NOTIFICATION-TYPE
		OBJECTS { trapCounter, tly3032c04v1Index, tly3032c04v1Gpi6 }
		STATUS current
		DESCRIPTION
			"GPI6 status Trap"
		::= { tly3032c04v1Traps 13 }

		-- 1.3.6.1.4.1.10106.2.1.1.478401.3
		tly3032c04v1Gpi7Trap NOTIFICATION-TYPE
		OBJECTS { trapCounter, tly3032c04v1Index, tly3032c04v1Gpi7 }
		STATUS current
		DESCRIPTION
			"GPI7 status Trap"
		::= { tly3032c04v1Traps 15 }

		-- 1.3.6.1.4.1.10106.2.1.1.478401.3
		tly3032c04v1Gpi8Trap NOTIFICATION-TYPE
		OBJECTS { trapCounter, tly3032c04v1Index, tly3032c04v1Gpi8 }
		STATUS current
		DESCRIPTION
			"GPI8 status Trap"
		::= { tly3032c04v1Traps 17 }

		-- 1.3.6.1.4.1.10106.2.1.1.478401.3
		tly3032c04v1Gpi9Trap NOTIFICATION-TYPE
		OBJECTS { trapCounter, tly3032c04v1Index, tly3032c04v1Gpi9 }
		STATUS current
		DESCRIPTION
			"GPI9 status Trap"
		::= { tly3032c04v1Traps 19 }

		-- 1.3.6.1.4.1.10106.2.1.1.478401.3
		tly3032c04v1Gpi10Trap NOTIFICATION-TYPE
		OBJECTS { trapCounter, tly3032c04v1Index, tly3032c04v1Gpi10 }
		STATUS current
		DESCRIPTION
			"GPI10 status Trap"
		::= { tly3032c04v1Traps 21 }

		-- 1.3.6.1.4.1.10106.2.1.1.478401.3
		tly3032c04v1Gpi11Trap NOTIFICATION-TYPE
		OBJECTS { trapCounter, tly3032c04v1Index, tly3032c04v1Gpi11 }
		STATUS current
		DESCRIPTION
			"GPI11 status Trap"
		::= { tly3032c04v1Traps 23 }

		-- 1.3.6.1.4.1.10106.2.1.1.478401.3
		tly3032c04v1Gpi12Trap NOTIFICATION-TYPE
		OBJECTS { trapCounter, tly3032c04v1Index, tly3032c04v1Gpi12 }
		STATUS current
		DESCRIPTION
			"GPI12 status Trap"
		::= { tly3032c04v1Traps 25 }

		-- 1.3.6.1.4.1.10106.2.1.1.478401.3
		tly3032c04v1Gpi13Trap NOTIFICATION-TYPE
		OBJECTS { trapCounter, tly3032c04v1Index, tly3032c04v1Gpi13 }
		STATUS current
		DESCRIPTION
			"GPI13 status Trap"
		::= { tly3032c04v1Traps 27 }

		-- 1.3.6.1.4.1.10106.2.1.1.478401.3
		tly3032c04v1Gpi14Trap NOTIFICATION-TYPE
		OBJECTS { trapCounter, tly3032c04v1Index, tly3032c04v1Gpi14 }
		STATUS current
		DESCRIPTION
			"GPI14 status Trap"
		::= { tly3032c04v1Traps 29 }

		-- 1.3.6.1.4.1.10106.2.1.1.478401.3
		tly3032c04v1Gpi15Trap NOTIFICATION-TYPE
		OBJECTS { trapCounter, tly3032c04v1Index, tly3032c04v1Gpi15 }
		STATUS current
		DESCRIPTION
			"GPI15 status Trap"
		::= { tly3032c04v1Traps 31 }

		-- 1.3.6.1.4.1.10106.2.1.1.478401.3
		tly3032c04v1Gpi16Trap NOTIFICATION-TYPE
		OBJECTS { trapCounter, tly3032c04v1Index, tly3032c04v1Gpi16 }
		STATUS current
		DESCRIPTION
			"GPI16 status Trap"
		::= { tly3032c04v1Traps 33 }

		-- 1.3.6.1.4.1.10106.2.1.1.478401.3
		tly3032c04v1Gpi17Trap NOTIFICATION-TYPE
		OBJECTS { trapCounter, tly3032c04v1Index, tly3032c04v1Gpi17 }
		STATUS current
		DESCRIPTION
			"GPI17 status Trap"
		::= { tly3032c04v1Traps 35 }

		-- 1.3.6.1.4.1.10106.2.1.1.478401.3
		tly3032c04v1Gpi18Trap NOTIFICATION-TYPE
		OBJECTS { trapCounter, tly3032c04v1Index, tly3032c04v1Gpi18 }
		STATUS current
		DESCRIPTION
			"GPI18 status Trap"
		::= { tly3032c04v1Traps 37 }

		-- 1.3.6.1.4.1.10106.2.1.1.478401.3
		tly3032c04v1Gpi19Trap NOTIFICATION-TYPE
		OBJECTS { trapCounter, tly3032c04v1Index, tly3032c04v1Gpi19 }
		STATUS current
		DESCRIPTION
			"GPI19 status Trap"
		::= { tly3032c04v1Traps 39 }

		-- 1.3.6.1.4.1.10106.2.1.1.478401.3
		tly3032c04v1Gpi20Trap NOTIFICATION-TYPE
		OBJECTS { trapCounter, tly3032c04v1Index, tly3032c04v1Gpi20 }
		STATUS current
		DESCRIPTION
			"GPI20 status Trap"
		::= { tly3032c04v1Traps 41 }

		-- 1.3.6.1.4.1.10106.2.1.1.478401.3
		tly3032c04v1Gpi21Trap NOTIFICATION-TYPE
		OBJECTS { trapCounter, tly3032c04v1Index, tly3032c04v1Gpi21 }
		STATUS current
		DESCRIPTION
			"GPI21 status Trap"
		::= { tly3032c04v1Traps 43 }

		-- 1.3.6.1.4.1.10106.2.1.1.478401.3
		tly3032c04v1Gpi22Trap NOTIFICATION-TYPE
		OBJECTS { trapCounter, tly3032c04v1Index, tly3032c04v1Gpi22 }
		STATUS current
		DESCRIPTION
			"GPI22 status Trap"
		::= { tly3032c04v1Traps 45 }

		-- 1.3.6.1.4.1.10106.2.1.1.478401.3
		tly3032c04v1Gpi23Trap NOTIFICATION-TYPE
		OBJECTS { trapCounter, tly3032c04v1Index, tly3032c04v1Gpi23 }
		STATUS current
		DESCRIPTION
			"GPI23 status Trap"
		::= { tly3032c04v1Traps 47 }

		-- 1.3.6.1.4.1.10106.2.1.1.478401.3
		tly3032c04v1Gpi24Trap NOTIFICATION-TYPE
		OBJECTS { trapCounter, tly3032c04v1Index, tly3032c04v1Gpi24 }
		STATUS current
		DESCRIPTION
			"GPI24 status Trap"
		::= { tly3032c04v1Traps 49 }

		-- 1.3.6.1.4.1.10106.2.1.1.478401.3
		tly3032c04v1Gpi25Trap NOTIFICATION-TYPE
		OBJECTS { trapCounter, tly3032c04v1Index, tly3032c04v1Gpi25 }
		STATUS current
		DESCRIPTION
			"GPI25 status Trap"
		::= { tly3032c04v1Traps 51 }

		-- 1.3.6.1.4.1.10106.2.1.1.478401.3
		tly3032c04v1Gpi26Trap NOTIFICATION-TYPE
		OBJECTS { trapCounter, tly3032c04v1Index, tly3032c04v1Gpi26 }
		STATUS current
		DESCRIPTION
			"GPI26 status Trap"
		::= { tly3032c04v1Traps 53 }

		-- 1.3.6.1.4.1.10106.2.1.1.478401.3
		tly3032c04v1Gpi27Trap NOTIFICATION-TYPE
		OBJECTS { trapCounter, tly3032c04v1Index, tly3032c04v1Gpi27 }
		STATUS current
		DESCRIPTION
			"GPI27 status Trap"
		::= { tly3032c04v1Traps 55 }

		-- 1.3.6.1.4.1.10106.2.1.1.478401.3
		tly3032c04v1Gpi28Trap NOTIFICATION-TYPE
		OBJECTS { trapCounter, tly3032c04v1Index, tly3032c04v1Gpi28 }
		STATUS current
		DESCRIPTION
			"GPI28 status Trap"
		::= { tly3032c04v1Traps 57 }

		-- 1.3.6.1.4.1.10106.2.1.1.478401.3
		tly3032c04v1Gpi29Trap NOTIFICATION-TYPE
		OBJECTS { trapCounter, tly3032c04v1Index, tly3032c04v1Gpi29 }
		STATUS current
		DESCRIPTION
			"GPI29 status Trap"
		::= { tly3032c04v1Traps 59 }

		-- 1.3.6.1.4.1.10106.2.1.1.478401.3
		tly3032c04v1Gpi30Trap NOTIFICATION-TYPE
		OBJECTS { trapCounter, tly3032c04v1Index, tly3032c04v1Gpi30 }
		STATUS current
		DESCRIPTION
			"GPI30 status Trap"
		::= { tly3032c04v1Traps 61 }

		-- 1.3.6.1.4.1.10106.2.1.1.478401.3
		tly3032c04v1Gpi31Trap NOTIFICATION-TYPE
		OBJECTS { trapCounter, tly3032c04v1Index, tly3032c04v1Gpi31 }
		STATUS current
		DESCRIPTION
			"GPI31 status Trap"
		::= { tly3032c04v1Traps 63 }

		-- 1.3.6.1.4.1.10106.2.1.1.478401.3
		tly3032c04v1Gpi32Trap NOTIFICATION-TYPE
		OBJECTS { trapCounter, tly3032c04v1Index, tly3032c04v1Gpi32 }
		STATUS current
		DESCRIPTION
			"GPI32 status Trap"
		::= { tly3032c04v1Traps 65 }

		-- 1.3.6.1.4.1.10106.2.1.1.478901
		tle0001c02v1Traps OBJECT IDENTIFIER ::= { albalaTraps 478901 }

		-- 1.3.6.1.4.1.10106.2.1.1.478901.3
		tle0001c02v1App1EnaTrap NOTIFICATION-TYPE
		OBJECTS { trapCounter, tle0001c02v1Index, tle0001c02v1App1Ena }
		STATUS current
		DESCRIPTION
			"Indicates the event log is enabled Trap"
		::= { tle0001c02v1Traps 5 }

		-- 1.3.6.1.4.1.10106.2.1.1.483501
		udp2000c01v1Traps OBJECT IDENTIFIER ::= { albalaTraps 483501 }

		-- 1.3.6.1.4.1.10106.2.1.1.483501.3
		udp2000c01v1NoSignalTrap NOTIFICATION-TYPE
		OBJECTS { trapCounter, udp2000c01v1Index, udp2000c01v1NoSignal }
		STATUS current
		DESCRIPTION
			"There is no SDI signal or the format is not supported Trap"
		::= { udp2000c01v1Traps 65 }

		-- 1.3.6.1.4.1.10106.2.1.1.483501.3
		udp2000c01v1UnlockTrap NOTIFICATION-TYPE
		OBJECTS { trapCounter, udp2000c01v1Index, udp2000c01v1Unlock }
		STATUS current
		DESCRIPTION
			"Indicates signal unlock fail Trap"
		::= { udp2000c01v1Traps 67 }

		-- 1.3.6.1.4.1.10106.2.1.1.483501.3
		udp2000c01v1DestAvailableTrap NOTIFICATION-TYPE
		OBJECTS { trapCounter, udp2000c01v1Index, udp2000c01v1DestAvailable }
		STATUS current
		DESCRIPTION
			"Destination IP available Trap"
		::= { udp2000c01v1Traps 73 }

		-- 1.3.6.1.4.1.10106.2.1.1.483501.3
		udp2000c01v1PingStatusTrap NOTIFICATION-TYPE
		OBJECTS { trapCounter, udp2000c01v1Index, udp2000c01v1PingStatus }
		STATUS current
		DESCRIPTION
			"Ping status Trap"
		::= { udp2000c01v1Traps 75 }

		-- 1.3.6.1.4.1.10106.2.1.1.483501.3
		udp2000c01v1EmbedderFailTrap NOTIFICATION-TYPE
		OBJECTS { trapCounter, udp2000c01v1Index, udp2000c01v1EmbedderFail }
		STATUS current
		DESCRIPTION
			"Embedder fail Trap"
		::= { udp2000c01v1Traps 77 }

		-- 1.3.6.1.4.1.10106.2.1.1.483501.3
		udp2000c01v1DeembedderFailTrap NOTIFICATION-TYPE
		OBJECTS { trapCounter, udp2000c01v1Index, udp2000c01v1DeembedderFail }
		STATUS current
		DESCRIPTION
			"Deembedder fail Trap"
		::= { udp2000c01v1Traps 79 }

		-- 1.3.6.1.4.1.10106.2.1.1.483501.3
		udp2000c01v1EmbedderValidTrap NOTIFICATION-TYPE
		OBJECTS { trapCounter, udp2000c01v1Index, udp2000c01v1EmbedderValid }
		STATUS current
		DESCRIPTION
			"Embedder RX valid Trap"
		::= { udp2000c01v1Traps 81 }

		-- 1.3.6.1.4.1.10106.2.1.1.483501.3
		udp2000c01v1DeembedderValidTrap NOTIFICATION-TYPE
		OBJECTS { trapCounter, udp2000c01v1Index, udp2000c01v1DeembedderValid }
		STATUS current
		DESCRIPTION
			"Deembedder RX valid Trap"
		::= { udp2000c01v1Traps 83 }

		-- 1.3.6.1.4.1.10106.2.1.1.483501.3
		udp2000c01v1VitcAtcPresTrap NOTIFICATION-TYPE
		OBJECTS { trapCounter, udp2000c01v1Index, udp2000c01v1VitcAtcPres }
		STATUS current
		DESCRIPTION
			"Input VITC-ATC presence Trap"
		::= { udp2000c01v1Traps 89 }

		-- 1.3.6.1.4.1.10106.2.1.1.484901
		aem2008c01v1Traps OBJECT IDENTIFIER ::= { albalaTraps 484901 }

		-- 1.3.6.1.4.1.10106.2.1.1.484901.3
		aem2008c01v1SdiInFailTrap NOTIFICATION-TYPE
		OBJECTS { trapCounter, aem2008c01v1Index, aem2008c01v1SdiInFail }
		STATUS current
		DESCRIPTION
			"SDI input signal status Trap"
		::= { aem2008c01v1Traps 11 }

		-- 1.3.6.1.4.1.10106.2.1.1.484901.3
		aem2008c01v1EdhInFailTrap NOTIFICATION-TYPE
		OBJECTS { trapCounter, aem2008c01v1Index, aem2008c01v1EdhInFail }
		STATUS current
		DESCRIPTION
			"It indicates EDH errors Trap"
		::= { aem2008c01v1Traps 13 }

		-- 1.3.6.1.4.1.10106.2.1.1.484901.3
		aem2008c01v1AudFailTrap NOTIFICATION-TYPE
		OBJECTS { trapCounter, aem2008c01v1Index, aem2008c01v1AudFail }
		STATUS current
		DESCRIPTION
			"It indicates there are audio errors Trap"
		::= { aem2008c01v1Traps 15 }

		-- 1.3.6.1.4.1.10106.2.1.1.484901.3
		aem2008c01v1AudClipTrap NOTIFICATION-TYPE
		OBJECTS { trapCounter, aem2008c01v1Index, aem2008c01v1AudClip }
		STATUS current
		DESCRIPTION
			"It indicates there is analogue clipping at the analogue inputs or digital clipping due to applied gain Trap"
		::= { aem2008c01v1Traps 17 }

		-- 1.3.6.1.4.1.10106.2.1.1.485001
		ade2008c01v1Traps OBJECT IDENTIFIER ::= { albalaTraps 485001 }

		-- 1.3.6.1.4.1.10106.2.1.1.485001.3
		ade2008c01v1SdiInFailTrap NOTIFICATION-TYPE
		OBJECTS { trapCounter, ade2008c01v1Index, ade2008c01v1SdiInFail }
		STATUS current
		DESCRIPTION
			"SDI input signal status Trap"
		::= { ade2008c01v1Traps 11 }

		-- 1.3.6.1.4.1.10106.2.1.1.485001.3
		ade2008c01v1EdhInFailTrap NOTIFICATION-TYPE
		OBJECTS { trapCounter, ade2008c01v1Index, ade2008c01v1EdhInFail }
		STATUS current
		DESCRIPTION
			"It indicates EDH errors Trap"
		::= { ade2008c01v1Traps 13 }

		-- 1.3.6.1.4.1.10106.2.1.1.485001.3
		ade2008c01v1AudFailTrap NOTIFICATION-TYPE
		OBJECTS { trapCounter, ade2008c01v1Index, ade2008c01v1AudFail }
		STATUS current
		DESCRIPTION
			"It indicates there are audio errors Trap"
		::= { ade2008c01v1Traps 15 }

		-- 1.3.6.1.4.1.10106.2.1.1.485001.3
		ade2008c01v1AudClipTrap NOTIFICATION-TYPE
		OBJECTS { trapCounter, ade2008c01v1Index, ade2008c01v1AudClip }
		STATUS current
		DESCRIPTION
			"It indicates there is digital clipping due to applied gain Trap"
		::= { ade2008c01v1Traps 17 }

		-- 1.3.6.1.4.1.10106.2.1.1.485901
		htg3001c01v1Traps OBJECT IDENTIFIER ::= { albalaTraps 485901 }

		-- 1.3.6.1.4.1.10106.2.1.1.485901.3
		htg3001c01v1ExpRefFormatTrap NOTIFICATION-TYPE
		OBJECTS { trapCounter, htg3001c01v1Index, htg3001c01v1ExpRefFormat }
		STATUS current
		DESCRIPTION
			"Allows selecting the expected format of the reference Trap"
		::= { htg3001c01v1Traps 3 }

		-- 1.3.6.1.4.1.10106.2.1.1.485901.3
		htg3001c01v1RefInputTrap NOTIFICATION-TYPE
		OBJECTS { trapCounter, htg3001c01v1Index, htg3001c01v1RefInput }
		STATUS current
		DESCRIPTION
			"Allows selecting the reference input Trap"
		::= { htg3001c01v1Traps 5 }

		-- 1.3.6.1.4.1.10106.2.1.1.485901.3
		htg3001c01v1OutFormat1Trap NOTIFICATION-TYPE
		OBJECTS { trapCounter, htg3001c01v1Index, htg3001c01v1OutFormat1 }
		STATUS current
		DESCRIPTION
			"Allows selecting the output format Trap"
		::= { htg3001c01v1Traps 9 }

		-- 1.3.6.1.4.1.10106.2.1.1.485901.3
		htg3001c01v1OutFormat2Trap NOTIFICATION-TYPE
		OBJECTS { trapCounter, htg3001c01v1Index, htg3001c01v1OutFormat2 }
		STATUS current
		DESCRIPTION
			"Allows selecting the output format Trap"
		::= { htg3001c01v1Traps 77 }

		-- 1.3.6.1.4.1.10106.2.1.1.485901.3
		htg3001c01v1OutFormat3Trap NOTIFICATION-TYPE
		OBJECTS { trapCounter, htg3001c01v1Index, htg3001c01v1OutFormat3 }
		STATUS current
		DESCRIPTION
			"Allows selecting the output format Trap"
		::= { htg3001c01v1Traps 145 }

		-- 1.3.6.1.4.1.10106.2.1.1.485901.3
		htg3001c01v1ArefFailTrap NOTIFICATION-TYPE
		OBJECTS { trapCounter, htg3001c01v1Index, htg3001c01v1ArefFail }
		STATUS current
		DESCRIPTION
			"Indicates the absence of analog reference Trap"
		::= { htg3001c01v1Traps 195 }

		-- 1.3.6.1.4.1.10106.2.1.1.485901.3
		htg3001c01v1DrefFailTrap NOTIFICATION-TYPE
		OBJECTS { trapCounter, htg3001c01v1Index, htg3001c01v1DrefFail }
		STATUS current
		DESCRIPTION
			"Indicates the absence of digital reference Trap"
		::= { htg3001c01v1Traps 197 }

		-- 1.3.6.1.4.1.10106.2.1.1.485901.3
		htg3001c01v1IrefFailTrap NOTIFICATION-TYPE
		OBJECTS { trapCounter, htg3001c01v1Index, htg3001c01v1IrefFail }
		STATUS current
		DESCRIPTION
			"Indicates the absence of internal reference Trap"
		::= { htg3001c01v1Traps 199 }

		-- 1.3.6.1.4.1.10106.2.1.1.485901.3
		htg3001c01v1RefIncFailTrap NOTIFICATION-TYPE
		OBJECTS { trapCounter, htg3001c01v1Index, htg3001c01v1RefIncFail }
		STATUS current
		DESCRIPTION
			"Indicates that the format of the received reference is different from expected Trap"
		::= { htg3001c01v1Traps 201 }

		-- 1.3.6.1.4.1.10106.2.1.1.485901.3
		htg3001c01v1RefLockFailTrap NOTIFICATION-TYPE
		OBJECTS { trapCounter, htg3001c01v1Index, htg3001c01v1RefLockFail }
		STATUS current
		DESCRIPTION
			"Indicates that the module is not locked to the reference Trap"
		::= { htg3001c01v1Traps 203 }

		-- 1.3.6.1.4.1.10106.2.1.1.485901.3
		htg3001c01v1DrefCrcFailTrap NOTIFICATION-TYPE
		OBJECTS { trapCounter, htg3001c01v1Index, htg3001c01v1DrefCrcFail }
		STATUS current
		DESCRIPTION
			"Indicates that the digital reference has CRC/EDH errors Trap"
		::= { htg3001c01v1Traps 205 }

		-- 1.3.6.1.4.1.10106.2.1.1.485901.3
		htg3001c01v1ArefFormatTrap NOTIFICATION-TYPE
		OBJECTS { trapCounter, htg3001c01v1Index, htg3001c01v1ArefFormat }
		STATUS current
		DESCRIPTION
			"Indicates the detected format of the analog reference Trap"
		::= { htg3001c01v1Traps 209 }

		-- 1.3.6.1.4.1.10106.2.1.1.485901.3
		htg3001c01v1DrefFormatTrap NOTIFICATION-TYPE
		OBJECTS { trapCounter, htg3001c01v1Index, htg3001c01v1DrefFormat }
		STATUS current
		DESCRIPTION
			"Indicates the detected format of the digital reference Trap"
		::= { htg3001c01v1Traps 211 }

		-- 1.3.6.1.4.1.10106.2.1.1.494401
		psu3300c03v1Traps OBJECT IDENTIFIER ::= { albalaTraps 494401 }

		-- 1.3.6.1.4.1.10106.2.1.1.494401.3
		psu3300c03v1PowerOffTrap NOTIFICATION-TYPE
		OBJECTS { trapCounter, psu3300c03v1Index, psu3300c03v1PowerOff }
		STATUS current
		DESCRIPTION
			"Indicates the power supply status Trap"
		::= { psu3300c03v1Traps 3 }

		-- 1.3.6.1.4.1.10106.2.1.1.494401.3
		psu3300c03v1TempWarningTrap NOTIFICATION-TYPE
		OBJECTS { trapCounter, psu3300c03v1Index, psu3300c03v1TempWarning }
		STATUS current
		DESCRIPTION
			"Indicates that actual temperature is over expected range Trap"
		::= { psu3300c03v1Traps 5 }

		-- 1.3.6.1.4.1.10106.2.1.1.494401.3
		psu3300c03v1TempFailTrap NOTIFICATION-TYPE
		OBJECTS { trapCounter, psu3300c03v1Index, psu3300c03v1TempFail }
		STATUS current
		DESCRIPTION
			"Indicates that actual temperature is over recommended range Trap"
		::= { psu3300c03v1Traps 7 }

		-- 1.3.6.1.4.1.10106.2.1.1.496001
		ttd3000c03v1Traps OBJECT IDENTIFIER ::= { albalaTraps 496001 }

		-- 1.3.6.1.4.1.10106.2.1.1.496001.3
		ttd3000c03v1ModeTrap NOTIFICATION-TYPE
		OBJECTS { trapCounter, ttd3000c03v1Index, ttd3000c03v1Mode }
		STATUS current
		DESCRIPTION
			"Allows selecting the switching mode Trap"
		::= { ttd3000c03v1Traps 3 }

		-- 1.3.6.1.4.1.10106.2.1.1.496001.3
		ttd3000c03v1InputATrap NOTIFICATION-TYPE
		OBJECTS { trapCounter, ttd3000c03v1Index, ttd3000c03v1InputA }
		STATUS current
		DESCRIPTION
			"Selected input Trap"
		::= { ttd3000c03v1Traps 5 }

		-- 1.3.6.1.4.1.10106.2.1.1.496001.3
		ttd3000c03v1InputBTrap NOTIFICATION-TYPE
		OBJECTS { trapCounter, ttd3000c03v1Index, ttd3000c03v1InputB }
		STATUS current
		DESCRIPTION
			"Selected input Trap"
		::= { ttd3000c03v1Traps 7 }

		-- 1.3.6.1.4.1.10106.2.1.1.496001.3
		ttd3000c03v1InputALvFailTrap NOTIFICATION-TYPE
		OBJECTS { trapCounter, ttd3000c03v1Index, ttd3000c03v1InputALvFail }
		STATUS current
		DESCRIPTION
			"Indicates signal presence fail Trap"
		::= { ttd3000c03v1Traps 17 }

		-- 1.3.6.1.4.1.10106.2.1.1.496001.3
		ttd3000c03v1InputAFrFailTrap NOTIFICATION-TYPE
		OBJECTS { trapCounter, ttd3000c03v1Index, ttd3000c03v1InputAFrFail }
		STATUS current
		DESCRIPTION
			"Indicates signal frequency fail Trap"
		::= { ttd3000c03v1Traps 19 }

		-- 1.3.6.1.4.1.10106.2.1.1.496001.3
		ttd3000c03v1InputBLbFailTrap NOTIFICATION-TYPE
		OBJECTS { trapCounter, ttd3000c03v1Index, ttd3000c03v1InputBLbFail }
		STATUS current
		DESCRIPTION
			"Indicates signal presence fail Trap"
		::= { ttd3000c03v1Traps 21 }

		-- 1.3.6.1.4.1.10106.2.1.1.496001.3
		ttd3000c03v1InputBFrFailTrap NOTIFICATION-TYPE
		OBJECTS { trapCounter, ttd3000c03v1Index, ttd3000c03v1InputBFrFail }
		STATUS current
		DESCRIPTION
			"Indicates signal frequency fail Trap"
		::= { ttd3000c03v1Traps 23 }

		-- 1.3.6.1.4.1.10106.2.1.1.497501
		adb2008c01v1Traps OBJECT IDENTIFIER ::= { albalaTraps 497501 }

		-- 1.3.6.1.4.1.10106.2.1.1.497501.3
		adb2008c01v1BusTimFailTrap NOTIFICATION-TYPE
		OBJECTS { trapCounter, adb2008c01v1Index, adb2008c01v1BusTimFail }
		STATUS current
		DESCRIPTION
			"Synchronization internal rack bus fail Trap"
		::= { adb2008c01v1Traps 49 }

		-- 1.3.6.1.4.1.10106.2.1.1.497501.3
		adb2008c01v1BusTimUnlckTrap NOTIFICATION-TYPE
		OBJECTS { trapCounter, adb2008c01v1Index, adb2008c01v1BusTimUnlck }
		STATUS current
		DESCRIPTION
			"Synchronization internal rack bus unlocked Trap"
		::= { adb2008c01v1Traps 51 }

		-- 1.3.6.1.4.1.10106.2.1.1.497501.3
		adb2008c01v1BusAudFailTrap NOTIFICATION-TYPE
		OBJECTS { trapCounter, adb2008c01v1Index, adb2008c01v1BusAudFail }
		STATUS current
		DESCRIPTION
			"Audio bus fail Trap"
		::= { adb2008c01v1Traps 53 }

		-- 1.3.6.1.4.1.10106.2.1.1.497501.3
		adb2008c01v1BusAudErrorTrap NOTIFICATION-TYPE
		OBJECTS { trapCounter, adb2008c01v1Index, adb2008c01v1BusAudError }
		STATUS current
		DESCRIPTION
			"Audio bus errors Trap"
		::= { adb2008c01v1Traps 55 }

		-- 1.3.6.1.4.1.10106.2.1.1.497501.3
		adb2008c01v1AudClipErTrap NOTIFICATION-TYPE
		OBJECTS { trapCounter, adb2008c01v1Index, adb2008c01v1AudClipEr }
		STATUS current
		DESCRIPTION
			"Audio clipping error Trap"
		::= { adb2008c01v1Traps 57 }

		-- 1.3.6.1.4.1.10106.2.1.1.497501.3
		adb2008c01v1AudInsFailTrap NOTIFICATION-TYPE
		OBJECTS { trapCounter, adb2008c01v1Index, adb2008c01v1AudInsFail }
		STATUS current
		DESCRIPTION
			"It lights up when the module cannot insert in the backplane bus the audio channels Trap"
		::= { adb2008c01v1Traps 59 }

		-- 1.3.6.1.4.1.10106.2.1.1.497501.3
		adb2008c01v1AudOvldFailTrap NOTIFICATION-TYPE
		OBJECTS { trapCounter, adb2008c01v1Index, adb2008c01v1AudOvldFail }
		STATUS current
		DESCRIPTION
			"Audio overload fail Trap"
		::= { adb2008c01v1Traps 61 }

		-- 1.3.6.1.4.1.10106.2.1.1.497601
		dab2008c01v1Traps OBJECT IDENTIFIER ::= { albalaTraps 497601 }

		-- 1.3.6.1.4.1.10106.2.1.1.497601.3
		dab2008c01v1BusSyncFailTrap NOTIFICATION-TYPE
		OBJECTS { trapCounter, dab2008c01v1Index, dab2008c01v1BusSyncFail }
		STATUS current
		DESCRIPTION
			"Synchronization internal rack bus fail Trap"
		::= { dab2008c01v1Traps 17 }

		-- 1.3.6.1.4.1.10106.2.1.1.497601.3
		dab2008c01v1BusSyncUnlckTrap NOTIFICATION-TYPE
		OBJECTS { trapCounter, dab2008c01v1Index, dab2008c01v1BusSyncUnlck }
		STATUS current
		DESCRIPTION
			"Synchronization internal rack bus unlocked Trap"
		::= { dab2008c01v1Traps 19 }

		-- 1.3.6.1.4.1.10106.2.1.1.497601.3
		dab2008c01v1BusAudFailTrap NOTIFICATION-TYPE
		OBJECTS { trapCounter, dab2008c01v1Index, dab2008c01v1BusAudFail }
		STATUS current
		DESCRIPTION
			"Audio bus fail Trap"
		::= { dab2008c01v1Traps 21 }

		-- 1.3.6.1.4.1.10106.2.1.1.497601.3
		dab2008c01v1BusAudErrorTrap NOTIFICATION-TYPE
		OBJECTS { trapCounter, dab2008c01v1Index, dab2008c01v1BusAudError }
		STATUS current
		DESCRIPTION
			"Audio bus errors Trap"
		::= { dab2008c01v1Traps 23 }

		-- 1.3.6.1.4.1.10106.2.1.1.497601.3
		dab2008c01v1AudClipErTrap NOTIFICATION-TYPE
		OBJECTS { trapCounter, dab2008c01v1Index, dab2008c01v1AudClipEr }
		STATUS current
		DESCRIPTION
			"Audio clipping error Trap"
		::= { dab2008c01v1Traps 25 }

		-- 1.3.6.1.4.1.10106.2.1.1.497601.3
		dab2008c01v1AudPresFailTrap NOTIFICATION-TYPE
		OBJECTS { trapCounter, dab2008c01v1Index, dab2008c01v1AudPresFail }
		STATUS current
		DESCRIPTION
			"It lights up when the backplane bus does not have all the audio channels the module is required to read Trap"
		::= { dab2008c01v1Traps 27 }

		-- 1.3.6.1.4.1.10106.2.1.1.497601.3
		dab2008c01v1AudOvldFailTrap NOTIFICATION-TYPE
		OBJECTS { trapCounter, dab2008c01v1Index, dab2008c01v1AudOvldFail }
		STATUS current
		DESCRIPTION
			"Audio overload fail Trap"
		::= { dab2008c01v1Traps 29 }

		-- 1.3.6.1.4.1.10106.2.1.1.497701
		ddb2008c01v1Traps OBJECT IDENTIFIER ::= { albalaTraps 497701 }

		-- 1.3.6.1.4.1.10106.2.1.1.497701.3
		ddb2008c01v1BusTimFailTrap NOTIFICATION-TYPE
		OBJECTS { trapCounter, ddb2008c01v1Index, ddb2008c01v1BusTimFail }
		STATUS current
		DESCRIPTION
			"Synchronization internal rack bus fail Trap"
		::= { ddb2008c01v1Traps 83 }

		-- 1.3.6.1.4.1.10106.2.1.1.497701.3
		ddb2008c01v1BusTimUnlckTrap NOTIFICATION-TYPE
		OBJECTS { trapCounter, ddb2008c01v1Index, ddb2008c01v1BusTimUnlck }
		STATUS current
		DESCRIPTION
			"Synchronization internal rack bus unlocked Trap"
		::= { ddb2008c01v1Traps 85 }

		-- 1.3.6.1.4.1.10106.2.1.1.497701.3
		ddb2008c01v1BusAudFailTrap NOTIFICATION-TYPE
		OBJECTS { trapCounter, ddb2008c01v1Index, ddb2008c01v1BusAudFail }
		STATUS current
		DESCRIPTION
			"Audio bus fail Trap"
		::= { ddb2008c01v1Traps 87 }

		-- 1.3.6.1.4.1.10106.2.1.1.497701.3
		ddb2008c01v1BusAudErrorTrap NOTIFICATION-TYPE
		OBJECTS { trapCounter, ddb2008c01v1Index, ddb2008c01v1BusAudError }
		STATUS current
		DESCRIPTION
			"Audio bus errors Trap"
		::= { ddb2008c01v1Traps 89 }

		-- 1.3.6.1.4.1.10106.2.1.1.497701.3
		ddb2008c01v1AudClipErTrap NOTIFICATION-TYPE
		OBJECTS { trapCounter, ddb2008c01v1Index, ddb2008c01v1AudClipEr }
		STATUS current
		DESCRIPTION
			"Audio clipping error Trap"
		::= { ddb2008c01v1Traps 91 }

		-- 1.3.6.1.4.1.10106.2.1.1.497701.3
		ddb2008c01v1AudPresFailTrap NOTIFICATION-TYPE
		OBJECTS { trapCounter, ddb2008c01v1Index, ddb2008c01v1AudPresFail }
		STATUS current
		DESCRIPTION
			"It lights up when the backplane bus does not have all the audio channels the module is required to read Trap"
		::= { ddb2008c01v1Traps 93 }

		-- 1.3.6.1.4.1.10106.2.1.1.497701.3
		ddb2008c01v1AudInsFailTrap NOTIFICATION-TYPE
		OBJECTS { trapCounter, ddb2008c01v1Index, ddb2008c01v1AudInsFail }
		STATUS current
		DESCRIPTION
			"It lights up when the module cannot insert in the backplane bus the audio channels Trap"
		::= { ddb2008c01v1Traps 95 }

		-- 1.3.6.1.4.1.10106.2.1.1.497701.3
		ddb2008c01v1AudOvldErTrap NOTIFICATION-TYPE
		OBJECTS { trapCounter, ddb2008c01v1Index, ddb2008c01v1AudOvldEr }
		STATUS current
		DESCRIPTION
			"Audio overload fail Trap"
		::= { ddb2008c01v1Traps 97 }

		-- 1.3.6.1.4.1.10106.2.1.1.514901
		smc2000c01v1Traps OBJECT IDENTIFIER ::= { albalaTraps 514901 }

		-- 1.3.6.1.4.1.10106.2.1.1.514901.3
		smc2000c01v1SfpPresTrap NOTIFICATION-TYPE
		OBJECTS { trapCounter, smc2000c01v1Index, smc2000c01v1SfpPres }
		STATUS current
		DESCRIPTION
			"SFP module present Trap"
		::= { smc2000c01v1Traps 9 }

		-- 1.3.6.1.4.1.10106.2.1.1.514901.3
		smc2000c01v1SfpFailTrap NOTIFICATION-TYPE
		OBJECTS { trapCounter, smc2000c01v1Index, smc2000c01v1SfpFail }
		STATUS current
		DESCRIPTION
			"Indicates a laser fault Trap"
		::= { smc2000c01v1Traps 11 }

		-- 1.3.6.1.4.1.10106.2.1.1.514901.3
		smc2000c01v1SfpLosTrap NOTIFICATION-TYPE
		OBJECTS { trapCounter, smc2000c01v1Index, smc2000c01v1SfpLos }
		STATUS current
		DESCRIPTION
			"SFP loss of signal Trap"
		::= { smc2000c01v1Traps 13 }

		-- 1.3.6.1.4.1.10106.2.1.1.514901.3
		smc2000c01v1P1StatusTrap NOTIFICATION-TYPE
		OBJECTS { trapCounter, smc2000c01v1Index, smc2000c01v1P1Status }
		STATUS current
		DESCRIPTION
			"Ethernet connection status in Port 1 Trap"
		::= { smc2000c01v1Traps 17 }

		-- 1.3.6.1.4.1.10106.2.1.1.514901.3
		smc2000c01v1P2StatusTrap NOTIFICATION-TYPE
		OBJECTS { trapCounter, smc2000c01v1Index, smc2000c01v1P2Status }
		STATUS current
		DESCRIPTION
			"Ethernet connection status in Port 2 Trap"
		::= { smc2000c01v1Traps 19 }

		-- 1.3.6.1.4.1.10106.2.1.1.514901.3
		smc2000c01v1PoStatusTrap NOTIFICATION-TYPE
		OBJECTS { trapCounter, smc2000c01v1Index, smc2000c01v1PoStatus }
		STATUS current
		DESCRIPTION
			"Ethernet connection status in Optical Port Trap"
		::= { smc2000c01v1Traps 21 }

		-- 1.3.6.1.4.1.10106.2.1.1.517501
		gps2000c01v1Traps OBJECT IDENTIFIER ::= { albalaTraps 517501 }

		-- 1.3.6.1.4.1.10106.2.1.1.517501.3
		gps2000c01v1GnssLosTrap NOTIFICATION-TYPE
		OBJECTS { trapCounter, gps2000c01v1Index, gps2000c01v1GnssLos }
		STATUS current
		DESCRIPTION
			"GNSS loss of signal. To be cleared it has to be for 30 s in in 3D-FIX or Time mode Trap"
		::= { gps2000c01v1Traps 75 }

		-- 1.3.6.1.4.1.10106.2.1.1.517501.3
		gps2000c01v1GnssPpsLosTrap NOTIFICATION-TYPE
		OBJECTS { trapCounter, gps2000c01v1Index, gps2000c01v1GnssPpsLos }
		STATUS current
		DESCRIPTION
			"GNSS loss of PPS. It is cleared when the error of the PPS delivered by GNSS module is less than 5 ns. It is set when the delay is greater than 50 ns Trap"
		::= { gps2000c01v1Traps 77 }

		-- 1.3.6.1.4.1.10106.2.1.1.517501.3
		gps2000c01v1GnssUnlockTrap NOTIFICATION-TYPE
		OBJECTS { trapCounter, gps2000c01v1Index, gps2000c01v1GnssUnlock }
		STATUS current
		DESCRIPTION
			"GNSS PPS unlock. It is cleared when the error of the output PPS is less than 10 ns. It is set when the error is greater than 100 ns. Trap"
		::= { gps2000c01v1Traps 79 }

		-- 1.3.6.1.4.1.10106.2.1.1.517501.3
		gps2000c01v1GnssPpsErrTrap NOTIFICATION-TYPE
		OBJECTS { trapCounter, gps2000c01v1Index, gps2000c01v1GnssPpsErr }
		STATUS current
		DESCRIPTION
			"GNSS pulse error. It is cleared when the error of the output PPS is less than the value specified in 'GNSS valid PPS margin'. It is set when the error is greater than this value. Trap"
		::= { gps2000c01v1Traps 81 }

		-- 1.3.6.1.4.1.10106.2.1.1.517501.3
		gps2000c01v1PtpLosTrap NOTIFICATION-TYPE
		OBJECTS { trapCounter, gps2000c01v1Index, gps2000c01v1PtpLos }
		STATUS current
		DESCRIPTION
			"PTP loss of signal.It is cleared when the PTP module is in Slave or Uncalibrated mode Trap"
		::= { gps2000c01v1Traps 83 }

		-- 1.3.6.1.4.1.10106.2.1.1.517501.3
		gps2000c01v1PtpPpsLosTrap NOTIFICATION-TYPE
		OBJECTS { trapCounter, gps2000c01v1Index, gps2000c01v1PtpPpsLos }
		STATUS current
		DESCRIPTION
			"PTP loss of PPS. It is cleared after 30 s receiving a valid PPS from PTP module Trap"
		::= { gps2000c01v1Traps 85 }

		-- 1.3.6.1.4.1.10106.2.1.1.517501.3
		gps2000c01v1PtpUnlockTrap NOTIFICATION-TYPE
		OBJECTS { trapCounter, gps2000c01v1Index, gps2000c01v1PtpUnlock }
		STATUS current
		DESCRIPTION
			"PTP PPS unlock. It is cleared when the error of the output PPS is less than 25 ns. It is set when the error is greater than 250 ns. Trap"
		::= { gps2000c01v1Traps 87 }

		-- 1.3.6.1.4.1.10106.2.1.1.517501.3
		gps2000c01v1PtpPpsErrTrap NOTIFICATION-TYPE
		OBJECTS { trapCounter, gps2000c01v1Index, gps2000c01v1PtpPpsErr }
		STATUS current
		DESCRIPTION
			"PTP PPS error. It is cleared when the error of the output PPS is less than the value specified in 'PTP valid PPS margin'. It is set when the error is greater than this value. Trap"
		::= { gps2000c01v1Traps 89 }

		-- 1.3.6.1.4.1.10106.2.1.1.517501.3
		gps2000c01v1SyncStateTrap NOTIFICATION-TYPE
		OBJECTS { trapCounter, gps2000c01v1Index, gps2000c01v1SyncState }
		STATUS current
		DESCRIPTION
			"Indicates the synchronization state Trap"
		::= { gps2000c01v1Traps 91 }

		-- 1.3.6.1.4.1.10106.2.1.1.517501.3
		gps2000c01v1ValidPpsTrap NOTIFICATION-TYPE
		OBJECTS { trapCounter, gps2000c01v1Index, gps2000c01v1ValidPps }
		STATUS current
		DESCRIPTION
			"Indicates that the internally generated PPS signal has been phase aligned with an external reference (GNSS or PTP) Trap"
		::= { gps2000c01v1Traps 93 }

		-- 1.3.6.1.4.1.10106.2.1.1.517501.3
		gps2000c01v1ModuleActiveTrap NOTIFICATION-TYPE
		OBJECTS { trapCounter, gps2000c01v1Index, gps2000c01v1ModuleActive }
		STATUS current
		DESCRIPTION
			"Indicates that this module is the one that provides the reference signals Trap"
		::= { gps2000c01v1Traps 95 }

		-- 1.3.6.1.4.1.10106.2.1.1.517501.3
		gps2000c01v1RedSyncStateTrap NOTIFICATION-TYPE
		OBJECTS { trapCounter, gps2000c01v1Index, gps2000c01v1RedSyncState }
		STATUS current
		DESCRIPTION
			"Indicates the redundant module's synchronization state Trap"
		::= { gps2000c01v1Traps 97 }

		-- 1.3.6.1.4.1.10106.2.1.1.517501.3
		gps2000c01v1RedModuleTrap NOTIFICATION-TYPE
		OBJECTS { trapCounter, gps2000c01v1Index, gps2000c01v1RedModule }
		STATUS current
		DESCRIPTION
			"Indicates if the redundant module is present Trap"
		::= { gps2000c01v1Traps 99 }

		-- 1.3.6.1.4.1.10106.2.1.1.517501.3
		gps2000c01v1FixModeTrap NOTIFICATION-TYPE
		OBJECTS { trapCounter, gps2000c01v1Index, gps2000c01v1FixMode }
		STATUS current
		DESCRIPTION
			"GNSS receiver module satellite tracking mode Trap"
		::= { gps2000c01v1Traps 101 }

		-- 1.3.6.1.4.1.10106.2.1.1.517501.3
		gps2000c01v1PowerStatTrap NOTIFICATION-TYPE
		OBJECTS { trapCounter, gps2000c01v1Index, gps2000c01v1PowerStat }
		STATUS current
		DESCRIPTION
			"Indicates the power supply status Trap"
		::= { gps2000c01v1Traps 117 }

		-- 1.3.6.1.4.1.10106.2.1.1.517501.3
		gps2000c01v1AntennaStatTrap NOTIFICATION-TYPE
		OBJECTS { trapCounter, gps2000c01v1Index, gps2000c01v1AntennaStat }
		STATUS current
		DESCRIPTION
			"Indicates the antenna connection status Trap"
		::= { gps2000c01v1Traps 119 }

		-- 1.3.6.1.4.1.10106.2.1.1.517501.3
		gps2000c01v1EthLinkTrap NOTIFICATION-TYPE
		OBJECTS { trapCounter, gps2000c01v1Index, gps2000c01v1EthLink }
		STATUS current
		DESCRIPTION
			"Indicates that the Ethernet link is OK Trap"
		::= { gps2000c01v1Traps 121 }

		-- 1.3.6.1.4.1.10106.2.1.1.517501.3
		gps2000c01v1OnePpsStatTrap NOTIFICATION-TYPE
		OBJECTS { trapCounter, gps2000c01v1Index, gps2000c01v1OnePpsStat }
		STATUS current
		DESCRIPTION
			"Indicates that the module is delivering a valid PPS Trap"
		::= { gps2000c01v1Traps 127 }

		-- 1.3.6.1.4.1.10106.2.1.1.520301
		isw3000c01v1Traps OBJECT IDENTIFIER ::= { albalaTraps 520301 }

		-- 1.3.6.1.4.1.10106.2.1.1.520301.3
		isw3000c01v1ModeTrap NOTIFICATION-TYPE
		OBJECTS { trapCounter, isw3000c01v1Index, isw3000c01v1Mode }
		STATUS current
		DESCRIPTION
			"Allows selecting the switching mode Trap"
		::= { isw3000c01v1Traps 3 }

		-- 1.3.6.1.4.1.10106.2.1.1.520301.3
		isw3000c01v1DvbTModeTrap NOTIFICATION-TYPE
		OBJECTS { trapCounter, isw3000c01v1Index, isw3000c01v1DvbTMode }
		STATUS current
		DESCRIPTION
			"Selects DVB mode. Trap"
		::= { isw3000c01v1Traps 5 }

		-- 1.3.6.1.4.1.10106.2.1.1.520301.3
		isw3000c01v1InputTrap NOTIFICATION-TYPE
		OBJECTS { trapCounter, isw3000c01v1Index, isw3000c01v1Input }
		STATUS current
		DESCRIPTION
			"Selected TS Trap"
		::= { isw3000c01v1Traps 15 }

		-- 1.3.6.1.4.1.10106.2.1.1.520301.3
		isw3000c01v1OutDelayTrap NOTIFICATION-TYPE
		OBJECTS { trapCounter, isw3000c01v1Index, isw3000c01v1OutDelay }
		STATUS current
		DESCRIPTION
			"Output delay refered to 1PPS reference in DVB-T mode Trap"
		::= { isw3000c01v1Traps 21 }

		-- 1.3.6.1.4.1.10106.2.1.1.520301.3
		isw3000c01v1AsiMainPriorTrap NOTIFICATION-TYPE
		OBJECTS { trapCounter, isw3000c01v1Index, isw3000c01v1AsiMainPrior }
		STATUS current
		DESCRIPTION
			"Allows selecting the ASI main input priority Trap"
		::= { isw3000c01v1Traps 23 }

		-- 1.3.6.1.4.1.10106.2.1.1.520301.3
		isw3000c01v1AsiResPriorTrap NOTIFICATION-TYPE
		OBJECTS { trapCounter, isw3000c01v1Index, isw3000c01v1AsiResPrior }
		STATUS current
		DESCRIPTION
			"Allows selecting the ASI reserve input priority Trap"
		::= { isw3000c01v1Traps 25 }

		-- 1.3.6.1.4.1.10106.2.1.1.520301.3
		isw3000c01v1PacketDelayTrap NOTIFICATION-TYPE
		OBJECTS { trapCounter, isw3000c01v1Index, isw3000c01v1PacketDelay }
		STATUS current
		DESCRIPTION
			"Output delay in TS packets in Generic DVB mode Trap"
		::= { isw3000c01v1Traps 39 }

		-- 1.3.6.1.4.1.10106.2.1.1.520301.3
		isw3000c01v1Ch1SelectionTrap NOTIFICATION-TYPE
		OBJECTS { trapCounter, isw3000c01v1Index, isw3000c01v1Ch1Selection }
		STATUS current
		DESCRIPTION
			"Channel 1 input selection Trap"
		::= { isw3000c01v1Traps 59 }

		-- 1.3.6.1.4.1.10106.2.1.1.520301.3
		isw3000c01v1Ch2SelectionTrap NOTIFICATION-TYPE
		OBJECTS { trapCounter, isw3000c01v1Index, isw3000c01v1Ch2Selection }
		STATUS current
		DESCRIPTION
			"Channel 2 input selection Trap"
		::= { isw3000c01v1Traps 61 }

		-- 1.3.6.1.4.1.10106.2.1.1.520301.3
		isw3000c01v1OutDelay0Trap NOTIFICATION-TYPE
		OBJECTS { trapCounter, isw3000c01v1Index, isw3000c01v1OutDelay0 }
		STATUS current
		DESCRIPTION
			"Output time in advance refered to 1PPS or absolute time reference in DVB-T2 mode.  Seconds. Trap"
		::= { isw3000c01v1Traps 63 }

		-- 1.3.6.1.4.1.10106.2.1.1.520301.3
		isw3000c01v1OutDelay1Trap NOTIFICATION-TYPE
		OBJECTS { trapCounter, isw3000c01v1Index, isw3000c01v1OutDelay1 }
		STATUS current
		DESCRIPTION
			"Output time in advance refered to 1PPS or absolute time reference in DVB-T2 mode.  Miliseconds. Trap"
		::= { isw3000c01v1Traps 65 }

		-- 1.3.6.1.4.1.10106.2.1.1.520301.3
		isw3000c01v1DvbT2Lock1Trap NOTIFICATION-TYPE
		OBJECTS { trapCounter, isw3000c01v1Index, isw3000c01v1DvbT2Lock1 }
		STATUS current
		DESCRIPTION
			"DVB-T2 locked Trap"
		::= { isw3000c01v1Traps 227 }

		-- 1.3.6.1.4.1.10106.2.1.1.520301.3
		isw3000c01v1DvbT2Lock2Trap NOTIFICATION-TYPE
		OBJECTS { trapCounter, isw3000c01v1Index, isw3000c01v1DvbT2Lock2 }
		STATUS current
		DESCRIPTION
			"DVB-T2 locked Trap"
		::= { isw3000c01v1Traps 229 }

		-- 1.3.6.1.4.1.10106.2.1.1.520301.3
		isw3000c01v11ppsFailTrap NOTIFICATION-TYPE
		OBJECTS { trapCounter, isw3000c01v1Index, isw3000c01v11ppsFail }
		STATUS current
		DESCRIPTION
			"1PPS reference input status Trap"
		::= { isw3000c01v1Traps 247 }

		-- 1.3.6.1.4.1.10106.2.1.1.520301.3
		isw3000c01v110mhzFailTrap NOTIFICATION-TYPE
		OBJECTS { trapCounter, isw3000c01v1Index, isw3000c01v110mhzFail }
		STATUS current
		DESCRIPTION
			"10MHz reference input status Trap"
		::= { isw3000c01v1Traps 249 }

		-- 1.3.6.1.4.1.10106.2.1.1.520301.3
		isw3000c01v1OutputFailTrap NOTIFICATION-TYPE
		OBJECTS { trapCounter, isw3000c01v1Index, isw3000c01v1OutputFail }
		STATUS current
		DESCRIPTION
			"The output signal is not valid because all inputs failed Trap"
		::= { isw3000c01v1Traps 251 }

		-- 1.3.6.1.4.1.10106.2.1.1.520301.3
		isw3000c01v1Ts1DelWarTrap NOTIFICATION-TYPE
		OBJECTS { trapCounter, isw3000c01v1Index, isw3000c01v1Ts1DelWar }
		STATUS current
		DESCRIPTION
			"The delay is greater than the programmed output delay Trap"
		::= { isw3000c01v1Traps 253 }

		-- 1.3.6.1.4.1.10106.2.1.1.520301.3
		isw3000c01v1Ts2DelWarTrap NOTIFICATION-TYPE
		OBJECTS { trapCounter, isw3000c01v1Index, isw3000c01v1Ts2DelWar }
		STATUS current
		DESCRIPTION
			"The delay is greater than the programmed output delay Trap"
		::= { isw3000c01v1Traps 255 }

		-- 1.3.6.1.4.1.10106.2.1.1.520301.3
		isw3000c01v1ExtFail1Trap NOTIFICATION-TYPE
		OBJECTS { trapCounter, isw3000c01v1Index, isw3000c01v1ExtFail1 }
		STATUS current
		DESCRIPTION
			"External input fail status Trap"
		::= { isw3000c01v1Traps 257 }

		-- 1.3.6.1.4.1.10106.2.1.1.520301.3
		isw3000c01v1ExtFail2Trap NOTIFICATION-TYPE
		OBJECTS { trapCounter, isw3000c01v1Index, isw3000c01v1ExtFail2 }
		STATUS current
		DESCRIPTION
			"External input fail status Trap"
		::= { isw3000c01v1Traps 259 }

		-- 1.3.6.1.4.1.10106.2.1.1.520301.3
		isw3000c01v1GlobalSeamTrap NOTIFICATION-TYPE
		OBJECTS { trapCounter, isw3000c01v1Index, isw3000c01v1GlobalSeam }
		STATUS current
		DESCRIPTION
			"Global seamles switching capability Trap"
		::= { isw3000c01v1Traps 261 }

		-- 1.3.6.1.4.1.10106.2.1.1.520301.3
		isw3000c01v1SyncLossErr1Trap NOTIFICATION-TYPE
		OBJECTS { trapCounter, isw3000c01v1Index, isw3000c01v1SyncLossErr1 }
		STATUS current
		DESCRIPTION
			"Sync loss fail (Fist priority  parameter 1.1) Trap"
		::= { isw3000c01v1Traps 263 }

		-- 1.3.6.1.4.1.10106.2.1.1.520301.3
		isw3000c01v1SyncByteErr1Trap NOTIFICATION-TYPE
		OBJECTS { trapCounter, isw3000c01v1Index, isw3000c01v1SyncByteErr1 }
		STATUS current
		DESCRIPTION
			"Sync byte error (Fist priority  parameter 1.2) Trap"
		::= { isw3000c01v1Traps 265 }

		-- 1.3.6.1.4.1.10106.2.1.1.520301.3
		isw3000c01v1PatError1Trap NOTIFICATION-TYPE
		OBJECTS { trapCounter, isw3000c01v1Index, isw3000c01v1PatError1 }
		STATUS current
		DESCRIPTION
			"PAT error (Fist priority  parameter 1.3) Trap"
		::= { isw3000c01v1Traps 267 }

		-- 1.3.6.1.4.1.10106.2.1.1.520301.3
		isw3000c01v1CcError1Trap NOTIFICATION-TYPE
		OBJECTS { trapCounter, isw3000c01v1Index, isw3000c01v1CcError1 }
		STATUS current
		DESCRIPTION
			"Continuity counter error (Fist priority  parameter 1.4) Trap"
		::= { isw3000c01v1Traps 269 }

		-- 1.3.6.1.4.1.10106.2.1.1.520301.3
		isw3000c01v1PmtError1Trap NOTIFICATION-TYPE
		OBJECTS { trapCounter, isw3000c01v1Index, isw3000c01v1PmtError1 }
		STATUS current
		DESCRIPTION
			"PMT error (Fist priority  parameter 1.5) Trap"
		::= { isw3000c01v1Traps 271 }

		-- 1.3.6.1.4.1.10106.2.1.1.520301.3
		isw3000c01v1PidError1Trap NOTIFICATION-TYPE
		OBJECTS { trapCounter, isw3000c01v1Index, isw3000c01v1PidError1 }
		STATUS current
		DESCRIPTION
			"PID error (Fist priority  parameter 1.6) Trap"
		::= { isw3000c01v1Traps 273 }

		-- 1.3.6.1.4.1.10106.2.1.1.520301.3
		isw3000c01v1MipError1Trap NOTIFICATION-TYPE
		OBJECTS { trapCounter, isw3000c01v1Index, isw3000c01v1MipError1 }
		STATUS current
		DESCRIPTION
			"MIP error. DVB-T compliant Trap"
		::= { isw3000c01v1Traps 275 }

		-- 1.3.6.1.4.1.10106.2.1.1.520301.3
		isw3000c01v1GlobalError1Trap NOTIFICATION-TYPE
		OBJECTS { trapCounter, isw3000c01v1Index, isw3000c01v1GlobalError1 }
		STATUS current
		DESCRIPTION
			"Global fail Trap"
		::= { isw3000c01v1Traps 277 }

		-- 1.3.6.1.4.1.10106.2.1.1.520301.3
		isw3000c01v1SyncLossErr2Trap NOTIFICATION-TYPE
		OBJECTS { trapCounter, isw3000c01v1Index, isw3000c01v1SyncLossErr2 }
		STATUS current
		DESCRIPTION
			"Sync loss fail (Fist priority  parameter 1.1) Trap"
		::= { isw3000c01v1Traps 279 }

		-- 1.3.6.1.4.1.10106.2.1.1.520301.3
		isw3000c01v1SyncByteErr2Trap NOTIFICATION-TYPE
		OBJECTS { trapCounter, isw3000c01v1Index, isw3000c01v1SyncByteErr2 }
		STATUS current
		DESCRIPTION
			"Sync byte error (Fist priority  parameter 1.2) Trap"
		::= { isw3000c01v1Traps 281 }

		-- 1.3.6.1.4.1.10106.2.1.1.520301.3
		isw3000c01v1PatError2Trap NOTIFICATION-TYPE
		OBJECTS { trapCounter, isw3000c01v1Index, isw3000c01v1PatError2 }
		STATUS current
		DESCRIPTION
			"PAT error (Fist priority  parameter 1.3) Trap"
		::= { isw3000c01v1Traps 283 }

		-- 1.3.6.1.4.1.10106.2.1.1.520301.3
		isw3000c01v1CcError2Trap NOTIFICATION-TYPE
		OBJECTS { trapCounter, isw3000c01v1Index, isw3000c01v1CcError2 }
		STATUS current
		DESCRIPTION
			"Continuity counter error (Fist priority  parameter 1.4) Trap"
		::= { isw3000c01v1Traps 285 }

		-- 1.3.6.1.4.1.10106.2.1.1.520301.3
		isw3000c01v1PmtError2Trap NOTIFICATION-TYPE
		OBJECTS { trapCounter, isw3000c01v1Index, isw3000c01v1PmtError2 }
		STATUS current
		DESCRIPTION
			"PMT error (Fist priority  parameter 1.5) Trap"
		::= { isw3000c01v1Traps 287 }

		-- 1.3.6.1.4.1.10106.2.1.1.520301.3
		isw3000c01v1PidError2Trap NOTIFICATION-TYPE
		OBJECTS { trapCounter, isw3000c01v1Index, isw3000c01v1PidError2 }
		STATUS current
		DESCRIPTION
			"PID error (Fist priority  parameter 1.6) Trap"
		::= { isw3000c01v1Traps 289 }

		-- 1.3.6.1.4.1.10106.2.1.1.520301.3
		isw3000c01v1MipError2Trap NOTIFICATION-TYPE
		OBJECTS { trapCounter, isw3000c01v1Index, isw3000c01v1MipError2 }
		STATUS current
		DESCRIPTION
			"MIP error. DVB-T compliant Trap"
		::= { isw3000c01v1Traps 291 }

		-- 1.3.6.1.4.1.10106.2.1.1.520301.3
		isw3000c01v1GlobalError2Trap NOTIFICATION-TYPE
		OBJECTS { trapCounter, isw3000c01v1Index, isw3000c01v1GlobalError2 }
		STATUS current
		DESCRIPTION
			"Global fail Trap"
		::= { isw3000c01v1Traps 293 }

		-- 1.3.6.1.4.1.10106.2.1.1.520301.3
		isw3000c01v1Ts1TraffFailTrap NOTIFICATION-TYPE
		OBJECTS { trapCounter, isw3000c01v1Index, isw3000c01v1Ts1TraffFail }
		STATUS current
		DESCRIPTION
			"Bitrate status Trap"
		::= { isw3000c01v1Traps 371 }

		-- 1.3.6.1.4.1.10106.2.1.1.520301.3
		isw3000c01v1Ts1NullPFailTrap NOTIFICATION-TYPE
		OBJECTS { trapCounter, isw3000c01v1Index, isw3000c01v1Ts1NullPFail }
		STATUS current
		DESCRIPTION
			"Null packet rate status Trap"
		::= { isw3000c01v1Traps 373 }

		-- 1.3.6.1.4.1.10106.2.1.1.520301.3
		isw3000c01v1Ts2TraffFailTrap NOTIFICATION-TYPE
		OBJECTS { trapCounter, isw3000c01v1Index, isw3000c01v1Ts2TraffFail }
		STATUS current
		DESCRIPTION
			"Bitrate status Trap"
		::= { isw3000c01v1Traps 375 }

		-- 1.3.6.1.4.1.10106.2.1.1.520301.3
		isw3000c01v1Ts2NullPFailTrap NOTIFICATION-TYPE
		OBJECTS { trapCounter, isw3000c01v1Index, isw3000c01v1Ts2NullPFail }
		STATUS current
		DESCRIPTION
			"Null packet rate status Trap"
		::= { isw3000c01v1Traps 377 }

		-- 1.3.6.1.4.1.10106.2.1.1.520301.3
		isw3000c01v1OutDelayT2Trap NOTIFICATION-TYPE
		OBJECTS { trapCounter, isw3000c01v1Index, isw3000c01v1OutDelayT2 }
		STATUS current
		DESCRIPTION
			"Output delay in TS packets in DVB-T2 mode with null timestamp Trap"
		::= { isw3000c01v1Traps 393 }

		-- 1.3.6.1.4.1.10106.2.1.1.520302
		isw3000c01v2Traps OBJECT IDENTIFIER ::= { albalaTraps 520302 }

		-- 1.3.6.1.4.1.10106.2.1.1.520302.3
		isw3000c01v2ModeTrap NOTIFICATION-TYPE
		OBJECTS { trapCounter, isw3000c01v2Index, isw3000c01v2Mode }
		STATUS current
		DESCRIPTION
			"Allows selecting the switching mode Trap"
		::= { isw3000c01v2Traps 3 }

		-- 1.3.6.1.4.1.10106.2.1.1.520302.3
		isw3000c01v2DvbTModeTrap NOTIFICATION-TYPE
		OBJECTS { trapCounter, isw3000c01v2Index, isw3000c01v2DvbTMode }
		STATUS current
		DESCRIPTION
			"Selects DVB mode. Trap"
		::= { isw3000c01v2Traps 5 }

		-- 1.3.6.1.4.1.10106.2.1.1.520302.3
		isw3000c01v2InputTrap NOTIFICATION-TYPE
		OBJECTS { trapCounter, isw3000c01v2Index, isw3000c01v2Input }
		STATUS current
		DESCRIPTION
			"Selected TS Trap"
		::= { isw3000c01v2Traps 15 }

		-- 1.3.6.1.4.1.10106.2.1.1.520302.3
		isw3000c01v2OutDelayTrap NOTIFICATION-TYPE
		OBJECTS { trapCounter, isw3000c01v2Index, isw3000c01v2OutDelay }
		STATUS current
		DESCRIPTION
			"Output delay refered to 1PPS reference in DVB-T mode Trap"
		::= { isw3000c01v2Traps 21 }

		-- 1.3.6.1.4.1.10106.2.1.1.520302.3
		isw3000c01v2AsiMainPriorTrap NOTIFICATION-TYPE
		OBJECTS { trapCounter, isw3000c01v2Index, isw3000c01v2AsiMainPrior }
		STATUS current
		DESCRIPTION
			"Allows selecting the ASI main input priority Trap"
		::= { isw3000c01v2Traps 23 }

		-- 1.3.6.1.4.1.10106.2.1.1.520302.3
		isw3000c01v2AsiResPriorTrap NOTIFICATION-TYPE
		OBJECTS { trapCounter, isw3000c01v2Index, isw3000c01v2AsiResPrior }
		STATUS current
		DESCRIPTION
			"Allows selecting the ASI reserve input priority Trap"
		::= { isw3000c01v2Traps 25 }

		-- 1.3.6.1.4.1.10106.2.1.1.520302.3
		isw3000c01v2OutDelayT2Trap NOTIFICATION-TYPE
		OBJECTS { trapCounter, isw3000c01v2Index, isw3000c01v2OutDelayT2 }
		STATUS current
		DESCRIPTION
			"Output delay in TS packets in DVB-T2 mode with null timestamp Trap"
		::= { isw3000c01v2Traps 41 }

		-- 1.3.6.1.4.1.10106.2.1.1.520302.3
		isw3000c01v2PacketDelayTrap NOTIFICATION-TYPE
		OBJECTS { trapCounter, isw3000c01v2Index, isw3000c01v2PacketDelay }
		STATUS current
		DESCRIPTION
			"Output delay in TS packets in Generic DVB mode Trap"
		::= { isw3000c01v2Traps 43 }

		-- 1.3.6.1.4.1.10106.2.1.1.520302.3
		isw3000c01v2Ch1SelectionTrap NOTIFICATION-TYPE
		OBJECTS { trapCounter, isw3000c01v2Index, isw3000c01v2Ch1Selection }
		STATUS current
		DESCRIPTION
			"Channel 1 input selection Trap"
		::= { isw3000c01v2Traps 67 }

		-- 1.3.6.1.4.1.10106.2.1.1.520302.3
		isw3000c01v2Ch2SelectionTrap NOTIFICATION-TYPE
		OBJECTS { trapCounter, isw3000c01v2Index, isw3000c01v2Ch2Selection }
		STATUS current
		DESCRIPTION
			"Channel 2 input selection Trap"
		::= { isw3000c01v2Traps 69 }

		-- 1.3.6.1.4.1.10106.2.1.1.520302.3
		isw3000c01v2OutDelay0Trap NOTIFICATION-TYPE
		OBJECTS { trapCounter, isw3000c01v2Index, isw3000c01v2OutDelay0 }
		STATUS current
		DESCRIPTION
			"Output time in advance refered to 1PPS or absolute time reference in DVB-T2 mode.  Seconds. Trap"
		::= { isw3000c01v2Traps 73 }

		-- 1.3.6.1.4.1.10106.2.1.1.520302.3
		isw3000c01v2OutDelay1Trap NOTIFICATION-TYPE
		OBJECTS { trapCounter, isw3000c01v2Index, isw3000c01v2OutDelay1 }
		STATUS current
		DESCRIPTION
			"Output time in advance refered to 1PPS or absolute time reference in DVB-T2 mode.  Miliseconds. Trap"
		::= { isw3000c01v2Traps 75 }

		-- 1.3.6.1.4.1.10106.2.1.1.520302.3
		isw3000c01v2DvbT2Lock1Trap NOTIFICATION-TYPE
		OBJECTS { trapCounter, isw3000c01v2Index, isw3000c01v2DvbT2Lock1 }
		STATUS current
		DESCRIPTION
			"DVB-T2 locked Trap"
		::= { isw3000c01v2Traps 253 }

		-- 1.3.6.1.4.1.10106.2.1.1.520302.3
		isw3000c01v2DvbT2Lock2Trap NOTIFICATION-TYPE
		OBJECTS { trapCounter, isw3000c01v2Index, isw3000c01v2DvbT2Lock2 }
		STATUS current
		DESCRIPTION
			"DVB-T2 locked Trap"
		::= { isw3000c01v2Traps 255 }

		-- 1.3.6.1.4.1.10106.2.1.1.520302.3
		isw3000c01v2Ts1TraffFailTrap NOTIFICATION-TYPE
		OBJECTS { trapCounter, isw3000c01v2Index, isw3000c01v2Ts1TraffFail }
		STATUS current
		DESCRIPTION
			"Bitrate status Trap"
		::= { isw3000c01v2Traps 281 }

		-- 1.3.6.1.4.1.10106.2.1.1.520302.3
		isw3000c01v2Ts1NullPFailTrap NOTIFICATION-TYPE
		OBJECTS { trapCounter, isw3000c01v2Index, isw3000c01v2Ts1NullPFail }
		STATUS current
		DESCRIPTION
			"Null packet rate status Trap"
		::= { isw3000c01v2Traps 283 }

		-- 1.3.6.1.4.1.10106.2.1.1.520302.3
		isw3000c01v2Ts2TraffFailTrap NOTIFICATION-TYPE
		OBJECTS { trapCounter, isw3000c01v2Index, isw3000c01v2Ts2TraffFail }
		STATUS current
		DESCRIPTION
			"Bitrate status Trap"
		::= { isw3000c01v2Traps 285 }

		-- 1.3.6.1.4.1.10106.2.1.1.520302.3
		isw3000c01v2Ts2NullPFailTrap NOTIFICATION-TYPE
		OBJECTS { trapCounter, isw3000c01v2Index, isw3000c01v2Ts2NullPFail }
		STATUS current
		DESCRIPTION
			"Null packet rate status Trap"
		::= { isw3000c01v2Traps 287 }

		-- 1.3.6.1.4.1.10106.2.1.1.520302.3
		isw3000c01v21ppsFailTrap NOTIFICATION-TYPE
		OBJECTS { trapCounter, isw3000c01v2Index, isw3000c01v21ppsFail }
		STATUS current
		DESCRIPTION
			"1PPS reference input status Trap"
		::= { isw3000c01v2Traps 289 }

		-- 1.3.6.1.4.1.10106.2.1.1.520302.3
		isw3000c01v210mhzFailTrap NOTIFICATION-TYPE
		OBJECTS { trapCounter, isw3000c01v2Index, isw3000c01v210mhzFail }
		STATUS current
		DESCRIPTION
			"10MHz reference input status Trap"
		::= { isw3000c01v2Traps 291 }

		-- 1.3.6.1.4.1.10106.2.1.1.520302.3
		isw3000c01v2OutputFailTrap NOTIFICATION-TYPE
		OBJECTS { trapCounter, isw3000c01v2Index, isw3000c01v2OutputFail }
		STATUS current
		DESCRIPTION
			"The output signal is not valid because all inputs failed Trap"
		::= { isw3000c01v2Traps 293 }

		-- 1.3.6.1.4.1.10106.2.1.1.520302.3
		isw3000c01v2Ts1DelWarTrap NOTIFICATION-TYPE
		OBJECTS { trapCounter, isw3000c01v2Index, isw3000c01v2Ts1DelWar }
		STATUS current
		DESCRIPTION
			"The delay is greater than the programmed output delay Trap"
		::= { isw3000c01v2Traps 295 }

		-- 1.3.6.1.4.1.10106.2.1.1.520302.3
		isw3000c01v2Ts2DelWarTrap NOTIFICATION-TYPE
		OBJECTS { trapCounter, isw3000c01v2Index, isw3000c01v2Ts2DelWar }
		STATUS current
		DESCRIPTION
			"The delay is greater than the programmed output delay Trap"
		::= { isw3000c01v2Traps 297 }

		-- 1.3.6.1.4.1.10106.2.1.1.520302.3
		isw3000c01v2ExtFail1Trap NOTIFICATION-TYPE
		OBJECTS { trapCounter, isw3000c01v2Index, isw3000c01v2ExtFail1 }
		STATUS current
		DESCRIPTION
			"External input fail status Trap"
		::= { isw3000c01v2Traps 299 }

		-- 1.3.6.1.4.1.10106.2.1.1.520302.3
		isw3000c01v2ExtFail2Trap NOTIFICATION-TYPE
		OBJECTS { trapCounter, isw3000c01v2Index, isw3000c01v2ExtFail2 }
		STATUS current
		DESCRIPTION
			"External input fail status Trap"
		::= { isw3000c01v2Traps 301 }

		-- 1.3.6.1.4.1.10106.2.1.1.520302.3
		isw3000c01v2GlobalSeamTrap NOTIFICATION-TYPE
		OBJECTS { trapCounter, isw3000c01v2Index, isw3000c01v2GlobalSeam }
		STATUS current
		DESCRIPTION
			"Global seamles switching capability Trap"
		::= { isw3000c01v2Traps 303 }

		-- 1.3.6.1.4.1.10106.2.1.1.520302.3
		isw3000c01v2SyncLossErr1Trap NOTIFICATION-TYPE
		OBJECTS { trapCounter, isw3000c01v2Index, isw3000c01v2SyncLossErr1 }
		STATUS current
		DESCRIPTION
			"Sync loss fail (Fist priority  parameter 1.1) Trap"
		::= { isw3000c01v2Traps 305 }

		-- 1.3.6.1.4.1.10106.2.1.1.520302.3
		isw3000c01v2SyncByteErr1Trap NOTIFICATION-TYPE
		OBJECTS { trapCounter, isw3000c01v2Index, isw3000c01v2SyncByteErr1 }
		STATUS current
		DESCRIPTION
			"Sync byte error (Fist priority  parameter 1.2) Trap"
		::= { isw3000c01v2Traps 307 }

		-- 1.3.6.1.4.1.10106.2.1.1.520302.3
		isw3000c01v2PatError1Trap NOTIFICATION-TYPE
		OBJECTS { trapCounter, isw3000c01v2Index, isw3000c01v2PatError1 }
		STATUS current
		DESCRIPTION
			"PAT error (Fist priority  parameter 1.3) Trap"
		::= { isw3000c01v2Traps 309 }

		-- 1.3.6.1.4.1.10106.2.1.1.520302.3
		isw3000c01v2CcError1Trap NOTIFICATION-TYPE
		OBJECTS { trapCounter, isw3000c01v2Index, isw3000c01v2CcError1 }
		STATUS current
		DESCRIPTION
			"Continuity counter error (Fist priority  parameter 1.4) Trap"
		::= { isw3000c01v2Traps 311 }

		-- 1.3.6.1.4.1.10106.2.1.1.520302.3
		isw3000c01v2PmtError1Trap NOTIFICATION-TYPE
		OBJECTS { trapCounter, isw3000c01v2Index, isw3000c01v2PmtError1 }
		STATUS current
		DESCRIPTION
			"PMT error (Fist priority  parameter 1.5) Trap"
		::= { isw3000c01v2Traps 313 }

		-- 1.3.6.1.4.1.10106.2.1.1.520302.3
		isw3000c01v2PidError1Trap NOTIFICATION-TYPE
		OBJECTS { trapCounter, isw3000c01v2Index, isw3000c01v2PidError1 }
		STATUS current
		DESCRIPTION
			"PID error (Fist priority  parameter 1.6) Trap"
		::= { isw3000c01v2Traps 315 }

		-- 1.3.6.1.4.1.10106.2.1.1.520302.3
		isw3000c01v2MipError1Trap NOTIFICATION-TYPE
		OBJECTS { trapCounter, isw3000c01v2Index, isw3000c01v2MipError1 }
		STATUS current
		DESCRIPTION
			"MIP error. DVB-T compliant Trap"
		::= { isw3000c01v2Traps 317 }

		-- 1.3.6.1.4.1.10106.2.1.1.520302.3
		isw3000c01v2GlobalError1Trap NOTIFICATION-TYPE
		OBJECTS { trapCounter, isw3000c01v2Index, isw3000c01v2GlobalError1 }
		STATUS current
		DESCRIPTION
			"Global fail Trap"
		::= { isw3000c01v2Traps 319 }

		-- 1.3.6.1.4.1.10106.2.1.1.520302.3
		isw3000c01v2SyncLossErr2Trap NOTIFICATION-TYPE
		OBJECTS { trapCounter, isw3000c01v2Index, isw3000c01v2SyncLossErr2 }
		STATUS current
		DESCRIPTION
			"Sync loss fail (Fist priority  parameter 1.1) Trap"
		::= { isw3000c01v2Traps 323 }

		-- 1.3.6.1.4.1.10106.2.1.1.520302.3
		isw3000c01v2SyncByteErr2Trap NOTIFICATION-TYPE
		OBJECTS { trapCounter, isw3000c01v2Index, isw3000c01v2SyncByteErr2 }
		STATUS current
		DESCRIPTION
			"Sync byte error (Fist priority  parameter 1.2) Trap"
		::= { isw3000c01v2Traps 325 }

		-- 1.3.6.1.4.1.10106.2.1.1.520302.3
		isw3000c01v2PatError2Trap NOTIFICATION-TYPE
		OBJECTS { trapCounter, isw3000c01v2Index, isw3000c01v2PatError2 }
		STATUS current
		DESCRIPTION
			"PAT error (Fist priority  parameter 1.3) Trap"
		::= { isw3000c01v2Traps 327 }

		-- 1.3.6.1.4.1.10106.2.1.1.520302.3
		isw3000c01v2CcError2Trap NOTIFICATION-TYPE
		OBJECTS { trapCounter, isw3000c01v2Index, isw3000c01v2CcError2 }
		STATUS current
		DESCRIPTION
			"Continuity counter error (Fist priority  parameter 1.4) Trap"
		::= { isw3000c01v2Traps 329 }

		-- 1.3.6.1.4.1.10106.2.1.1.520302.3
		isw3000c01v2PmtError2Trap NOTIFICATION-TYPE
		OBJECTS { trapCounter, isw3000c01v2Index, isw3000c01v2PmtError2 }
		STATUS current
		DESCRIPTION
			"PMT error (Fist priority  parameter 1.5) Trap"
		::= { isw3000c01v2Traps 331 }

		-- 1.3.6.1.4.1.10106.2.1.1.520302.3
		isw3000c01v2PidError2Trap NOTIFICATION-TYPE
		OBJECTS { trapCounter, isw3000c01v2Index, isw3000c01v2PidError2 }
		STATUS current
		DESCRIPTION
			"PID error (Fist priority  parameter 1.6) Trap"
		::= { isw3000c01v2Traps 333 }

		-- 1.3.6.1.4.1.10106.2.1.1.520302.3
		isw3000c01v2MipError2Trap NOTIFICATION-TYPE
		OBJECTS { trapCounter, isw3000c01v2Index, isw3000c01v2MipError2 }
		STATUS current
		DESCRIPTION
			"MIP error. DVB-T compliant Trap"
		::= { isw3000c01v2Traps 335 }

		-- 1.3.6.1.4.1.10106.2.1.1.520302.3
		isw3000c01v2GlobalError2Trap NOTIFICATION-TYPE
		OBJECTS { trapCounter, isw3000c01v2Index, isw3000c01v2GlobalError2 }
		STATUS current
		DESCRIPTION
			"Global fail Trap"
		::= { isw3000c01v2Traps 337 }

		-- 1.3.6.1.4.1.10106.2.1.1.523601
		swc2000c01v1Traps OBJECT IDENTIFIER ::= { albalaTraps 523601 }

		-- 1.3.6.1.4.1.10106.2.1.1.523601.3
		swc2000c01v1Gpi1Trap NOTIFICATION-TYPE
		OBJECTS { trapCounter, swc2000c01v1Index, swc2000c01v1Gpi1 }
		STATUS current
		DESCRIPTION
			"GPI1 status Trap"
		::= { swc2000c01v1Traps 27 }

		-- 1.3.6.1.4.1.10106.2.1.1.523601.3
		swc2000c01v1Gpi2Trap NOTIFICATION-TYPE
		OBJECTS { trapCounter, swc2000c01v1Index, swc2000c01v1Gpi2 }
		STATUS current
		DESCRIPTION
			"GPI2 status Trap"
		::= { swc2000c01v1Traps 29 }

		-- 1.3.6.1.4.1.10106.2.1.1.523601.3
		swc2000c01v1Gpi3Trap NOTIFICATION-TYPE
		OBJECTS { trapCounter, swc2000c01v1Index, swc2000c01v1Gpi3 }
		STATUS current
		DESCRIPTION
			"GPI3 status Trap"
		::= { swc2000c01v1Traps 31 }

		-- 1.3.6.1.4.1.10106.2.1.1.523601.3
		swc2000c01v1Gpi4Trap NOTIFICATION-TYPE
		OBJECTS { trapCounter, swc2000c01v1Index, swc2000c01v1Gpi4 }
		STATUS current
		DESCRIPTION
			"GPI4 status Trap"
		::= { swc2000c01v1Traps 33 }

		-- 1.3.6.1.4.1.10106.2.1.1.523601.3
		swc2000c01v1RedBoardTrap NOTIFICATION-TYPE
		OBJECTS { trapCounter, swc2000c01v1Index, swc2000c01v1RedBoard }
		STATUS current
		DESCRIPTION
			"Indicates that there are two modules in redundant configuration Trap"
		::= { swc2000c01v1Traps 35 }

		-- 1.3.6.1.4.1.10106.2.1.1.523601.3
		swc2000c01v1EthLinkTrap NOTIFICATION-TYPE
		OBJECTS { trapCounter, swc2000c01v1Index, swc2000c01v1EthLink }
		STATUS current
		DESCRIPTION
			"Indicates that the Ethernet link is OK Trap"
		::= { swc2000c01v1Traps 37 }

		-- 1.3.6.1.4.1.10106.2.1.1.523601.3
		swc2000c01v1EthRedActTrap NOTIFICATION-TYPE
		OBJECTS { trapCounter, swc2000c01v1Index, swc2000c01v1EthRedAct }
		STATUS current
		DESCRIPTION
			"Indicates that this is the active module of the redundant configuration Trap"
		::= { swc2000c01v1Traps 39 }

		-- 1.3.6.1.4.1.10106.2.1.1.524101
		psu2001c01v1Traps OBJECT IDENTIFIER ::= { albalaTraps 524101 }

		-- 1.3.6.1.4.1.10106.2.1.1.524101.3
		psu2001c01v1PowerOffTrap NOTIFICATION-TYPE
		OBJECTS { trapCounter, psu2001c01v1Index, psu2001c01v1PowerOff }
		STATUS current
		DESCRIPTION
			"Indicates the power supply status Trap"
		::= { psu2001c01v1Traps 3 }

		-- 1.3.6.1.4.1.10106.2.1.1.524101.3
		psu2001c01v1TempWarningTrap NOTIFICATION-TYPE
		OBJECTS { trapCounter, psu2001c01v1Index, psu2001c01v1TempWarning }
		STATUS current
		DESCRIPTION
			"Indicates that actual temperature is over expected range Trap"
		::= { psu2001c01v1Traps 5 }

		-- 1.3.6.1.4.1.10106.2.1.1.524101.3
		psu2001c01v1TempFailTrap NOTIFICATION-TYPE
		OBJECTS { trapCounter, psu2001c01v1Index, psu2001c01v1TempFail }
		STATUS current
		DESCRIPTION
			"Indicates that actual temperature is over recommended range Trap"
		::= { psu2001c01v1Traps 7 }

		-- 1.3.6.1.4.1.10106.2.1.1.524101.3
		psu2001c01v1PwrWarningTrap NOTIFICATION-TYPE
		OBJECTS { trapCounter, psu2001c01v1Index, psu2001c01v1PwrWarning }
		STATUS current
		DESCRIPTION
			"Indicates that actual output power is over expected range Trap"
		::= { psu2001c01v1Traps 9 }

		-- 1.3.6.1.4.1.10106.2.1.1.524101.3
		psu2001c01v1PwrFailTrap NOTIFICATION-TYPE
		OBJECTS { trapCounter, psu2001c01v1Index, psu2001c01v1PwrFail }
		STATUS current
		DESCRIPTION
			"Indicates that actual output power is over allowed range Trap"
		::= { psu2001c01v1Traps 11 }

		-- 1.3.6.1.4.1.10106.2.1.1.527201
		eol2000c01v1Traps OBJECT IDENTIFIER ::= { albalaTraps 527201 }

		-- 1.3.6.1.4.1.10106.2.1.1.527201.3
		eol2000c01v1InFormat1Trap NOTIFICATION-TYPE
		OBJECTS { trapCounter, eol2000c01v1Index, eol2000c01v1InFormat1 }
		STATUS current
		DESCRIPTION
			"SDI signal format Trap"
		::= { eol2000c01v1Traps 19 }

		-- 1.3.6.1.4.1.10106.2.1.1.527201.3
		eol2000c01v1RefUnlockTrap NOTIFICATION-TYPE
		OBJECTS { trapCounter, eol2000c01v1Index, eol2000c01v1RefUnlock }
		STATUS current
		DESCRIPTION
			"Indicates reference signal unlock fail Trap"
		::= { eol2000c01v1Traps 23 }

		-- 1.3.6.1.4.1.10106.2.1.1.527201.3
		eol2000c01v1NoSigATrap NOTIFICATION-TYPE
		OBJECTS { trapCounter, eol2000c01v1Index, eol2000c01v1NoSigA }
		STATUS current
		DESCRIPTION
			"Indicates SDI signal fail Trap"
		::= { eol2000c01v1Traps 25 }

		-- 1.3.6.1.4.1.10106.2.1.1.527201.3
		eol2000c01v1NoSigBTrap NOTIFICATION-TYPE
		OBJECTS { trapCounter, eol2000c01v1Index, eol2000c01v1NoSigB }
		STATUS current
		DESCRIPTION
			"Indicates SDI signal fail Trap"
		::= { eol2000c01v1Traps 27 }

		-- 1.3.6.1.4.1.10106.2.1.1.527201.3
		eol2000c01v1SfpPresTrap NOTIFICATION-TYPE
		OBJECTS { trapCounter, eol2000c01v1Index, eol2000c01v1SfpPres }
		STATUS current
		DESCRIPTION
			"Indicates whether a compatible SFP transceiver is present Trap"
		::= { eol2000c01v1Traps 29 }

		-- 1.3.6.1.4.1.10106.2.1.1.529001
		ttd2000c01v1Traps OBJECT IDENTIFIER ::= { albalaTraps 529001 }

		-- 1.3.6.1.4.1.10106.2.1.1.529001.3
		ttd2000c01v1FrInputTrap NOTIFICATION-TYPE
		OBJECTS { trapCounter, ttd2000c01v1Index, ttd2000c01v1FrInput }
		STATUS current
		DESCRIPTION
			"Selected input Trap"
		::= { ttd2000c01v1Traps 3 }

		-- 1.3.6.1.4.1.10106.2.1.1.529001.3
		ttd2000c01v1Onepps12Trap NOTIFICATION-TYPE
		OBJECTS { trapCounter, ttd2000c01v1Index, ttd2000c01v1Onepps12 }
		STATUS current
		DESCRIPTION
			"Allows selecting the signal delivered to outputs 1 & 2 Trap"
		::= { ttd2000c01v1Traps 5 }

		-- 1.3.6.1.4.1.10106.2.1.1.529001.3
		ttd2000c01v1Onepps34Trap NOTIFICATION-TYPE
		OBJECTS { trapCounter, ttd2000c01v1Index, ttd2000c01v1Onepps34 }
		STATUS current
		DESCRIPTION
			"4  & 5 Trap"
		::= { ttd2000c01v1Traps 7 }

		-- 1.3.6.1.4.1.10106.2.1.1.529001.3
		ttd2000c01v1FrFailTrap NOTIFICATION-TYPE
		OBJECTS { trapCounter, ttd2000c01v1Index, ttd2000c01v1FrFail }
		STATUS current
		DESCRIPTION
			"Indicates front input signal fail Trap"
		::= { ttd2000c01v1Traps 13 }

		-- 1.3.6.1.4.1.10106.2.1.1.529001.3
		ttd2000c01v1ReTtlFailTrap NOTIFICATION-TYPE
		OBJECTS { trapCounter, ttd2000c01v1Index, ttd2000c01v1ReTtlFail }
		STATUS current
		DESCRIPTION
			"Indicates 1 PPS/48 kHz bus signal fail Trap"
		::= { ttd2000c01v1Traps 15 }

		-- 1.3.6.1.4.1.10106.2.1.1.529001.3
		ttd2000c01v1Re10mhzFailTrap NOTIFICATION-TYPE
		OBJECTS { trapCounter, ttd2000c01v1Index, ttd2000c01v1Re10mhzFail }
		STATUS current
		DESCRIPTION
			"Indicates 10 MHz bus signal fail Trap"
		::= { ttd2000c01v1Traps 17 }

		-- 1.3.6.1.4.1.10106.2.1.1.530801
		psu2100c01v1Traps OBJECT IDENTIFIER ::= { albalaTraps 530801 }

		-- 1.3.6.1.4.1.10106.2.1.1.530801.3
		psu2100c01v1PowerOffTrap NOTIFICATION-TYPE
		OBJECTS { trapCounter, psu2100c01v1Index, psu2100c01v1PowerOff }
		STATUS current
		DESCRIPTION
			"Indicates the power supply status Trap"
		::= { psu2100c01v1Traps 3 }

		-- 1.3.6.1.4.1.10106.2.1.1.530801.3
		psu2100c01v1TempWarningTrap NOTIFICATION-TYPE
		OBJECTS { trapCounter, psu2100c01v1Index, psu2100c01v1TempWarning }
		STATUS current
		DESCRIPTION
			"Indicates that actual temperature is over expected range Trap"
		::= { psu2100c01v1Traps 5 }

		-- 1.3.6.1.4.1.10106.2.1.1.530801.3
		psu2100c01v1TempFailTrap NOTIFICATION-TYPE
		OBJECTS { trapCounter, psu2100c01v1Index, psu2100c01v1TempFail }
		STATUS current
		DESCRIPTION
			"Indicates that actual temperature is over recommended range Trap"
		::= { psu2100c01v1Traps 7 }

		-- 1.3.6.1.4.1.10106.2.1.1.530801.3
		psu2100c01v1PwrWarningTrap NOTIFICATION-TYPE
		OBJECTS { trapCounter, psu2100c01v1Index, psu2100c01v1PwrWarning }
		STATUS current
		DESCRIPTION
			"Indicates that actual output power is over expected range Trap"
		::= { psu2100c01v1Traps 9 }

		-- 1.3.6.1.4.1.10106.2.1.1.530801.3
		psu2100c01v1PwrFailTrap NOTIFICATION-TYPE
		OBJECTS { trapCounter, psu2100c01v1Index, psu2100c01v1PwrFail }
		STATUS current
		DESCRIPTION
			"Indicates that actual output power is over allowed range Trap"
		::= { psu2100c01v1Traps 11 }

		-- 1.3.6.1.4.1.10106.2.1.1.538901
		atg2000c01v1Traps OBJECT IDENTIFIER ::= { albalaTraps 538901 }

		-- 1.3.6.1.4.1.10106.2.1.1.538901.3
		atg2000c01v1RefLockFailTrap NOTIFICATION-TYPE
		OBJECTS { trapCounter, atg2000c01v1Index, atg2000c01v1RefLockFail }
		STATUS current
		DESCRIPTION
			"Indicates that the module is not locked to the internal reference Trap"
		::= { atg2000c01v1Traps 51 }

		-- 1.3.6.1.4.1.10106.2.1.1.540801
		hvd2001c01v1Traps OBJECT IDENTIFIER ::= { albalaTraps 540801 }

		-- 1.3.6.1.4.1.10106.2.1.1.540801.3
		hvd2001c01v1NoSigTrap NOTIFICATION-TYPE
		OBJECTS { trapCounter, hvd2001c01v1Index, hvd2001c01v1NoSig }
		STATUS current
		DESCRIPTION
			"Input signal status Trap"
		::= { hvd2001c01v1Traps 3 }

		-- 1.3.6.1.4.1.10106.2.1.1.540801.3
		hvd2001c01v1UnlockTrap NOTIFICATION-TYPE
		OBJECTS { trapCounter, hvd2001c01v1Index, hvd2001c01v1Unlock }
		STATUS current
		DESCRIPTION
			"Indicates signal unlock fail Trap"
		::= { hvd2001c01v1Traps 5 }

		-- 1.3.6.1.4.1.10106.2.1.1.542501
		gti2000c01v1Traps OBJECT IDENTIFIER ::= { albalaTraps 542501 }

		-- 1.3.6.1.4.1.10106.2.1.1.542501.3
		gti2000c01v1ModeTrap NOTIFICATION-TYPE
		OBJECTS { trapCounter, gti2000c01v1Index, gti2000c01v1Mode }
		STATUS current
		DESCRIPTION
			"Allows selecting the switching mode Trap"
		::= { gti2000c01v1Traps 9 }

		-- 1.3.6.1.4.1.10106.2.1.1.542501.3
		gti2000c01v1InputTrap NOTIFICATION-TYPE
		OBJECTS { trapCounter, gti2000c01v1Index, gti2000c01v1Input }
		STATUS current
		DESCRIPTION
			"Allows selecting the reference input Trap"
		::= { gti2000c01v1Traps 13 }

		-- 1.3.6.1.4.1.10106.2.1.1.542501.3
		gti2000c01v1RearFailTrap NOTIFICATION-TYPE
		OBJECTS { trapCounter, gti2000c01v1Index, gti2000c01v1RearFail }
		STATUS current
		DESCRIPTION
			"Indicates lack of valid rear reference Trap"
		::= { gti2000c01v1Traps 23 }

		-- 1.3.6.1.4.1.10106.2.1.1.542501.3
		gti2000c01v1FrontFailTrap NOTIFICATION-TYPE
		OBJECTS { trapCounter, gti2000c01v1Index, gti2000c01v1FrontFail }
		STATUS current
		DESCRIPTION
			"Indicates lack of valid front reference Trap"
		::= { gti2000c01v1Traps 25 }

		-- 1.3.6.1.4.1.10106.2.1.1.542501.3
		gti2000c01v1UnlockTrap NOTIFICATION-TYPE
		OBJECTS { trapCounter, gti2000c01v1Index, gti2000c01v1Unlock }
		STATUS current
		DESCRIPTION
			"Reference lock fail Trap"
		::= { gti2000c01v1Traps 27 }

		-- 1.3.6.1.4.1.10106.2.1.1.552801
		tly2010c01v1Traps OBJECT IDENTIFIER ::= { albalaTraps 552801 }

		-- 1.3.6.1.4.1.10106.2.1.1.552801.3
		tly2010c01v1GpoTrap NOTIFICATION-TYPE
		OBJECTS { trapCounter, tly2010c01v1Index, tly2010c01v1Gpo }
		STATUS current
		DESCRIPTION
			"Activated GPO Trap"
		::= { tly2010c01v1Traps 3 }

		-- 1.3.6.1.4.1.10106.2.1.1.552801.3
		tly2010c01v1PhyGpoTrap NOTIFICATION-TYPE
		OBJECTS { trapCounter, tly2010c01v1Index, tly2010c01v1PhyGpo }
		STATUS current
		DESCRIPTION
			"Indicates the active GPO Trap"
		::= { tly2010c01v1Traps 11 }

		-- 1.3.6.1.4.1.10106.2.1.1.553101
		hli2000c01v1Traps OBJECT IDENTIFIER ::= { albalaTraps 553101 }

		-- 1.3.6.1.4.1.10106.2.1.1.553101.3
		hli2000c01v1RxFormatTrap NOTIFICATION-TYPE
		OBJECTS { trapCounter, hli2000c01v1Index, hli2000c01v1RxFormat }
		STATUS current
		DESCRIPTION
			"Indicates the SDI received signal format Trap"
		::= { hli2000c01v1Traps 223 }

		-- 1.3.6.1.4.1.10106.2.1.1.553101.3
		hli2000c01v1NoSignalTrap NOTIFICATION-TYPE
		OBJECTS { trapCounter, hli2000c01v1Index, hli2000c01v1NoSignal }
		STATUS current
		DESCRIPTION
			"There is no SDI signal or the format is not supported Trap"
		::= { hli2000c01v1Traps 227 }

		-- 1.3.6.1.4.1.10106.2.1.1.553101.3
		hli2000c01v1EdhCrcTrap NOTIFICATION-TYPE
		OBJECTS { trapCounter, hli2000c01v1Index, hli2000c01v1EdhCrc }
		STATUS current
		DESCRIPTION
			"Indicates presence of EDH/CRC errors Trap"
		::= { hli2000c01v1Traps 229 }

		-- 1.3.6.1.4.1.10106.2.1.1.553101.3
		hli2000c01v1LockFailTrap NOTIFICATION-TYPE
		OBJECTS { trapCounter, hli2000c01v1Index, hli2000c01v1LockFail }
		STATUS current
		DESCRIPTION
			"Output video is not locked to input Trap"
		::= { hli2000c01v1Traps 231 }

		-- 1.3.6.1.4.1.10106.2.1.1.553901
		vct2000c01v1Traps OBJECT IDENTIFIER ::= { albalaTraps 553901 }

		-- 1.3.6.1.4.1.10106.2.1.1.553901.3
		vct2000c01v1ModeTrap NOTIFICATION-TYPE
		OBJECTS { trapCounter, vct2000c01v1Index, vct2000c01v1Mode }
		STATUS current
		DESCRIPTION
			"Allows selecting the switching mode Trap"
		::= { vct2000c01v1Traps 3 }

		-- 1.3.6.1.4.1.10106.2.1.1.553901.3
		vct2000c01v1InputTrap NOTIFICATION-TYPE
		OBJECTS { trapCounter, vct2000c01v1Index, vct2000c01v1Input }
		STATUS current
		DESCRIPTION
			"Selected input Trap"
		::= { vct2000c01v1Traps 7 }

		-- 1.3.6.1.4.1.10106.2.1.1.553901.3
		vct2000c01v1InpMainFailTrap NOTIFICATION-TYPE
		OBJECTS { trapCounter, vct2000c01v1Index, vct2000c01v1InpMainFail }
		STATUS current
		DESCRIPTION
			"Main input status Trap"
		::= { vct2000c01v1Traps 15 }

		-- 1.3.6.1.4.1.10106.2.1.1.553901.3
		vct2000c01v1GpiMainFailTrap NOTIFICATION-TYPE
		OBJECTS { trapCounter, vct2000c01v1Index, vct2000c01v1GpiMainFail }
		STATUS current
		DESCRIPTION
			"GPI main input status Trap"
		::= { vct2000c01v1Traps 17 }

		-- 1.3.6.1.4.1.10106.2.1.1.553901.3
		vct2000c01v1InpResFailTrap NOTIFICATION-TYPE
		OBJECTS { trapCounter, vct2000c01v1Index, vct2000c01v1InpResFail }
		STATUS current
		DESCRIPTION
			"Reserve input status Trap"
		::= { vct2000c01v1Traps 19 }

		-- 1.3.6.1.4.1.10106.2.1.1.553901.3
		vct2000c01v1GpiResFailTrap NOTIFICATION-TYPE
		OBJECTS { trapCounter, vct2000c01v1Index, vct2000c01v1GpiResFail }
		STATUS current
		DESCRIPTION
			"GPI main input status Trap"
		::= { vct2000c01v1Traps 21 }

		-- 1.3.6.1.4.1.10106.2.1.1.554501
		hxc2000c01v1Traps OBJECT IDENTIFIER ::= { albalaTraps 554501 }

		-- 1.3.6.1.4.1.10106.2.1.1.554501.3
		hxc2000c01v1AnaRefFmtTrap NOTIFICATION-TYPE
		OBJECTS { trapCounter, hxc2000c01v1Index, hxc2000c01v1AnaRefFmt }
		STATUS current
		DESCRIPTION
			"Analog reference input format Trap"
		::= { hxc2000c01v1Traps 9 }

		-- 1.3.6.1.4.1.10106.2.1.1.554501.3
		hxc2000c01v1ModeConvTrap NOTIFICATION-TYPE
		OBJECTS { trapCounter, hxc2000c01v1Index, hxc2000c01v1ModeConv }
		STATUS current
		DESCRIPTION
			"Conversion mode Trap"
		::= { hxc2000c01v1Traps 17 }

		-- 1.3.6.1.4.1.10106.2.1.1.554501.3
		hxc2000c01v1OutAfdTrap NOTIFICATION-TYPE
		OBJECTS { trapCounter, hxc2000c01v1Index, hxc2000c01v1OutAfd }
		STATUS current
		DESCRIPTION
			"Output active format description Trap"
		::= { hxc2000c01v1Traps 19 }

		-- 1.3.6.1.4.1.10106.2.1.1.554501.3
		hxc2000c01v1OutCfTrap NOTIFICATION-TYPE
		OBJECTS { trapCounter, hxc2000c01v1Index, hxc2000c01v1OutCf }
		STATUS current
		DESCRIPTION
			"Output coded frame Trap"
		::= { hxc2000c01v1Traps 21 }

		-- 1.3.6.1.4.1.10106.2.1.1.554501.3
		hxc2000c01v1InAfdExpctTrap NOTIFICATION-TYPE
		OBJECTS { trapCounter, hxc2000c01v1Index, hxc2000c01v1InAfdExpct }
		STATUS current
		DESCRIPTION
			"Input expected active format description Trap"
		::= { hxc2000c01v1Traps 25 }

		-- 1.3.6.1.4.1.10106.2.1.1.554501.3
		hxc2000c01v1InCfExpctTrap NOTIFICATION-TYPE
		OBJECTS { trapCounter, hxc2000c01v1Index, hxc2000c01v1InCfExpct }
		STATUS current
		DESCRIPTION
			"Input expected coded frame Trap"
		::= { hxc2000c01v1Traps 27 }

		-- 1.3.6.1.4.1.10106.2.1.1.554501.3
		hxc2000c01v1TxFmtTrap NOTIFICATION-TYPE
		OBJECTS { trapCounter, hxc2000c01v1Index, hxc2000c01v1TxFmt }
		STATUS current
		DESCRIPTION
			"Output format Trap"
		::= { hxc2000c01v1Traps 29 }

		-- 1.3.6.1.4.1.10106.2.1.1.554501.3
		hxc2000c01v1DeintAlgorithmTrap NOTIFICATION-TYPE
		OBJECTS { trapCounter, hxc2000c01v1Index, hxc2000c01v1DeintAlgorithm }
		STATUS current
		DESCRIPTION
			"Allows selecting the de-interlacing algorithm Trap"
		::= { hxc2000c01v1Traps 31 }

		-- 1.3.6.1.4.1.10106.2.1.1.554501.3
		hxc2000c01v1InPhyFailTrap NOTIFICATION-TYPE
		OBJECTS { trapCounter, hxc2000c01v1Index, hxc2000c01v1InPhyFail }
		STATUS current
		DESCRIPTION
			"Absence fail Trap"
		::= { hxc2000c01v1Traps 101 }

		-- 1.3.6.1.4.1.10106.2.1.1.554501.3
		hxc2000c01v1InFmtFailTrap NOTIFICATION-TYPE
		OBJECTS { trapCounter, hxc2000c01v1Index, hxc2000c01v1InFmtFail }
		STATUS current
		DESCRIPTION
			"Format fail Trap"
		::= { hxc2000c01v1Traps 103 }

		-- 1.3.6.1.4.1.10106.2.1.1.554501.3
		hxc2000c01v1InIncFailTrap NOTIFICATION-TYPE
		OBJECTS { trapCounter, hxc2000c01v1Index, hxc2000c01v1InIncFail }
		STATUS current
		DESCRIPTION
			"Incompatible format fail Trap"
		::= { hxc2000c01v1Traps 105 }

		-- 1.3.6.1.4.1.10106.2.1.1.554501.3
		hxc2000c01v1InCrcFailTrap NOTIFICATION-TYPE
		OBJECTS { trapCounter, hxc2000c01v1Index, hxc2000c01v1InCrcFail }
		STATUS current
		DESCRIPTION
			"EDH/CRC fail Trap"
		::= { hxc2000c01v1Traps 109 }

		-- 1.3.6.1.4.1.10106.2.1.1.554501.3
		hxc2000c01v1PresAudG1FailTrap NOTIFICATION-TYPE
		OBJECTS { trapCounter, hxc2000c01v1Index, hxc2000c01v1PresAudG1Fail }
		STATUS current
		DESCRIPTION
			"Audio group 1 presence fail Trap"
		::= { hxc2000c01v1Traps 119 }

		-- 1.3.6.1.4.1.10106.2.1.1.554501.3
		hxc2000c01v1PresAudG2FailTrap NOTIFICATION-TYPE
		OBJECTS { trapCounter, hxc2000c01v1Index, hxc2000c01v1PresAudG2Fail }
		STATUS current
		DESCRIPTION
			"Audio group 2 presence fail Trap"
		::= { hxc2000c01v1Traps 121 }

		-- 1.3.6.1.4.1.10106.2.1.1.554501.3
		hxc2000c01v1PresAudG3FailTrap NOTIFICATION-TYPE
		OBJECTS { trapCounter, hxc2000c01v1Index, hxc2000c01v1PresAudG3Fail }
		STATUS current
		DESCRIPTION
			"Audio group 3 presence fail Trap"
		::= { hxc2000c01v1Traps 123 }

		-- 1.3.6.1.4.1.10106.2.1.1.554501.3
		hxc2000c01v1PresAudG4FailTrap NOTIFICATION-TYPE
		OBJECTS { trapCounter, hxc2000c01v1Index, hxc2000c01v1PresAudG4Fail }
		STATUS current
		DESCRIPTION
			"Audio group 4 presence fail Trap"
		::= { hxc2000c01v1Traps 125 }

		-- 1.3.6.1.4.1.10106.2.1.1.554501.3
		hxc2000c01v1RefFailTrap NOTIFICATION-TYPE
		OBJECTS { trapCounter, hxc2000c01v1Index, hxc2000c01v1RefFail }
		STATUS current
		DESCRIPTION
			"Analog reference absence fail Trap"
		::= { hxc2000c01v1Traps 127 }

		-- 1.3.6.1.4.1.10106.2.1.1.554501.3
		hxc2000c01v1RefFmtFailTrap NOTIFICATION-TYPE
		OBJECTS { trapCounter, hxc2000c01v1Index, hxc2000c01v1RefFmtFail }
		STATUS current
		DESCRIPTION
			"Analog reference format fail Trap"
		::= { hxc2000c01v1Traps 129 }

		-- 1.3.6.1.4.1.10106.2.1.1.554501.3
		hxc2000c01v1LockFailTrap NOTIFICATION-TYPE
		OBJECTS { trapCounter, hxc2000c01v1Index, hxc2000c01v1LockFail }
		STATUS current
		DESCRIPTION
			"Reference unlock fail Trap"
		::= { hxc2000c01v1Traps 131 }

		-- 1.3.6.1.4.1.10106.2.1.1.554501.3
		hxc2000c01v1AudPair0FailTrap NOTIFICATION-TYPE
		OBJECTS { trapCounter, hxc2000c01v1Index, hxc2000c01v1AudPair0Fail }
		STATUS current
		DESCRIPTION
			"Audio pair 0 fail Trap"
		::= { hxc2000c01v1Traps 133 }

		-- 1.3.6.1.4.1.10106.2.1.1.554501.3
		hxc2000c01v1AudPair1FailTrap NOTIFICATION-TYPE
		OBJECTS { trapCounter, hxc2000c01v1Index, hxc2000c01v1AudPair1Fail }
		STATUS current
		DESCRIPTION
			"Audio pair 1 fail Trap"
		::= { hxc2000c01v1Traps 135 }

		-- 1.3.6.1.4.1.10106.2.1.1.554501.3
		hxc2000c01v1AudPair2FailTrap NOTIFICATION-TYPE
		OBJECTS { trapCounter, hxc2000c01v1Index, hxc2000c01v1AudPair2Fail }
		STATUS current
		DESCRIPTION
			"Audio pair 2 fail Trap"
		::= { hxc2000c01v1Traps 137 }

		-- 1.3.6.1.4.1.10106.2.1.1.554501.3
		hxc2000c01v1AudPair3FailTrap NOTIFICATION-TYPE
		OBJECTS { trapCounter, hxc2000c01v1Index, hxc2000c01v1AudPair3Fail }
		STATUS current
		DESCRIPTION
			"Audio pair 3 fail Trap"
		::= { hxc2000c01v1Traps 139 }

		-- 1.3.6.1.4.1.10106.2.1.1.554501.3
		hxc2000c01v1AudPair4FailTrap NOTIFICATION-TYPE
		OBJECTS { trapCounter, hxc2000c01v1Index, hxc2000c01v1AudPair4Fail }
		STATUS current
		DESCRIPTION
			"Audio pair 4 fail Trap"
		::= { hxc2000c01v1Traps 141 }

		-- 1.3.6.1.4.1.10106.2.1.1.554501.3
		hxc2000c01v1AudPair5FailTrap NOTIFICATION-TYPE
		OBJECTS { trapCounter, hxc2000c01v1Index, hxc2000c01v1AudPair5Fail }
		STATUS current
		DESCRIPTION
			"Audio pair 5 fail Trap"
		::= { hxc2000c01v1Traps 143 }

		-- 1.3.6.1.4.1.10106.2.1.1.554501.3
		hxc2000c01v1AudPair6FailTrap NOTIFICATION-TYPE
		OBJECTS { trapCounter, hxc2000c01v1Index, hxc2000c01v1AudPair6Fail }
		STATUS current
		DESCRIPTION
			"Audio pair 6 fail Trap"
		::= { hxc2000c01v1Traps 145 }

		-- 1.3.6.1.4.1.10106.2.1.1.554501.3
		hxc2000c01v1AudPair7FailTrap NOTIFICATION-TYPE
		OBJECTS { trapCounter, hxc2000c01v1Index, hxc2000c01v1AudPair7Fail }
		STATUS current
		DESCRIPTION
			"Audio pair 7 fail Trap"
		::= { hxc2000c01v1Traps 147 }

		-- 1.3.6.1.4.1.10106.2.1.1.554501.3
		hxc2000c01v1InAfdDetctTrap NOTIFICATION-TYPE
		OBJECTS { trapCounter, hxc2000c01v1Index, hxc2000c01v1InAfdDetct }
		STATUS current
		DESCRIPTION
			"Input detected AFD Trap"
		::= { hxc2000c01v1Traps 149 }

		-- 1.3.6.1.4.1.10106.2.1.1.554501.3
		hxc2000c01v1InCfDetctTrap NOTIFICATION-TYPE
		OBJECTS { trapCounter, hxc2000c01v1Index, hxc2000c01v1InCfDetct }
		STATUS current
		DESCRIPTION
			"Input detected coded frame Trap"
		::= { hxc2000c01v1Traps 151 }

		-- 1.3.6.1.4.1.10106.2.1.1.554501.3
		hxc2000c01v1InFormatTrap NOTIFICATION-TYPE
		OBJECTS { trapCounter, hxc2000c01v1Index, hxc2000c01v1InFormat }
		STATUS current
		DESCRIPTION
			"Input format Trap"
		::= { hxc2000c01v1Traps 153 }

		-- 1.3.6.1.4.1.10106.2.1.1.554501.3
		hxc2000c01v1RefFormatTrap NOTIFICATION-TYPE
		OBJECTS { trapCounter, hxc2000c01v1Index, hxc2000c01v1RefFormat }
		STATUS current
		DESCRIPTION
			"Reference format Trap"
		::= { hxc2000c01v1Traps 155 }

		-- 1.3.6.1.4.1.10106.2.1.1.554501.3
		hxc2000c01v1TxFormatTrap NOTIFICATION-TYPE
		OBJECTS { trapCounter, hxc2000c01v1Index, hxc2000c01v1TxFormat }
		STATUS current
		DESCRIPTION
			"Output format Trap"
		::= { hxc2000c01v1Traps 157 }

		-- 1.3.6.1.4.1.10106.2.1.1.555601
		uop2000c01v1Traps OBJECT IDENTIFIER ::= { albalaTraps 555601 }

		-- 1.3.6.1.4.1.10106.2.1.1.555601.3
		uop2000c01v1InputATrap NOTIFICATION-TYPE
		OBJECTS { trapCounter, uop2000c01v1Index, uop2000c01v1InputA }
		STATUS current
		DESCRIPTION
			"Indicates the input selected Trap"
		::= { uop2000c01v1Traps 3 }

		-- 1.3.6.1.4.1.10106.2.1.1.555601.3
		uop2000c01v1InputBTrap NOTIFICATION-TYPE
		OBJECTS { trapCounter, uop2000c01v1Index, uop2000c01v1InputB }
		STATUS current
		DESCRIPTION
			"Indicates the input selected Trap"
		::= { uop2000c01v1Traps 5 }

		-- 1.3.6.1.4.1.10106.2.1.1.555601.3
		uop2000c01v1LosATrap NOTIFICATION-TYPE
		OBJECTS { trapCounter, uop2000c01v1Index, uop2000c01v1LosA }
		STATUS current
		DESCRIPTION
			"Indicates a loss of signal Trap"
		::= { uop2000c01v1Traps 15 }

		-- 1.3.6.1.4.1.10106.2.1.1.555601.3
		uop2000c01v1UnlockATrap NOTIFICATION-TYPE
		OBJECTS { trapCounter, uop2000c01v1Index, uop2000c01v1UnlockA }
		STATUS current
		DESCRIPTION
			"Indicates signal unlock fail Trap"
		::= { uop2000c01v1Traps 17 }

		-- 1.3.6.1.4.1.10106.2.1.1.555601.3
		uop2000c01v1RateATrap NOTIFICATION-TYPE
		OBJECTS { trapCounter, uop2000c01v1Index, uop2000c01v1RateA }
		STATUS current
		DESCRIPTION
			"Indicates the SDI signal type Trap"
		::= { uop2000c01v1Traps 19 }

		-- 1.3.6.1.4.1.10106.2.1.1.555601.3
		uop2000c01v1LosBTrap NOTIFICATION-TYPE
		OBJECTS { trapCounter, uop2000c01v1Index, uop2000c01v1LosB }
		STATUS current
		DESCRIPTION
			"Indicates a loss of signal Trap"
		::= { uop2000c01v1Traps 21 }

		-- 1.3.6.1.4.1.10106.2.1.1.555601.3
		uop2000c01v1UnlockBTrap NOTIFICATION-TYPE
		OBJECTS { trapCounter, uop2000c01v1Index, uop2000c01v1UnlockB }
		STATUS current
		DESCRIPTION
			"Indicates signal unlock fail Trap"
		::= { uop2000c01v1Traps 23 }

		-- 1.3.6.1.4.1.10106.2.1.1.555601.3
		uop2000c01v1RateBTrap NOTIFICATION-TYPE
		OBJECTS { trapCounter, uop2000c01v1Index, uop2000c01v1RateB }
		STATUS current
		DESCRIPTION
			"Indicates the SDI signal type Trap"
		::= { uop2000c01v1Traps 25 }

		-- 1.3.6.1.4.1.10106.2.1.1.574401
		act2000c01v1Traps OBJECT IDENTIFIER ::= { albalaTraps 574401 }

		-- 1.3.6.1.4.1.10106.2.1.1.574401.3
		act2000c01v1ModeTrap NOTIFICATION-TYPE
		OBJECTS { trapCounter, act2000c01v1Index, act2000c01v1Mode }
		STATUS current
		DESCRIPTION
			"Allows selecting the switching mode Trap"
		::= { act2000c01v1Traps 3 }

		-- 1.3.6.1.4.1.10106.2.1.1.574401.3
		act2000c01v1InputTrap NOTIFICATION-TYPE
		OBJECTS { trapCounter, act2000c01v1Index, act2000c01v1Input }
		STATUS current
		DESCRIPTION
			"Selected input Trap"
		::= { act2000c01v1Traps 7 }

		-- 1.3.6.1.4.1.10106.2.1.1.574401.3
		act2000c01v1InpMainFailTrap NOTIFICATION-TYPE
		OBJECTS { trapCounter, act2000c01v1Index, act2000c01v1InpMainFail }
		STATUS current
		DESCRIPTION
			"Main input status Trap"
		::= { act2000c01v1Traps 19 }

		-- 1.3.6.1.4.1.10106.2.1.1.574401.3
		act2000c01v1GpiMainFailTrap NOTIFICATION-TYPE
		OBJECTS { trapCounter, act2000c01v1Index, act2000c01v1GpiMainFail }
		STATUS current
		DESCRIPTION
			"GPI main input status Trap"
		::= { act2000c01v1Traps 21 }

		-- 1.3.6.1.4.1.10106.2.1.1.574401.3
		act2000c01v1InpResFailTrap NOTIFICATION-TYPE
		OBJECTS { trapCounter, act2000c01v1Index, act2000c01v1InpResFail }
		STATUS current
		DESCRIPTION
			"Reserve input status Trap"
		::= { act2000c01v1Traps 23 }

		-- 1.3.6.1.4.1.10106.2.1.1.574401.3
		act2000c01v1GpiResFailTrap NOTIFICATION-TYPE
		OBJECTS { trapCounter, act2000c01v1Index, act2000c01v1GpiResFail }
		STATUS current
		DESCRIPTION
			"GPI main input status Trap"
		::= { act2000c01v1Traps 25 }

		-- 1.3.6.1.4.1.10106.2.1.1.577901
		utg2000c01v1Traps OBJECT IDENTIFIER ::= { albalaTraps 577901 }

		-- 1.3.6.1.4.1.10106.2.1.1.577901.3
		utg2000c01v1ExpRefFormatTrap NOTIFICATION-TYPE
		OBJECTS { trapCounter, utg2000c01v1Index, utg2000c01v1ExpRefFormat }
		STATUS current
		DESCRIPTION
			"Allows selecting the expected format of the reference Trap"
		::= { utg2000c01v1Traps 17 }

		-- 1.3.6.1.4.1.10106.2.1.1.577901.3
		utg2000c01v1RefInputTrap NOTIFICATION-TYPE
		OBJECTS { trapCounter, utg2000c01v1Index, utg2000c01v1RefInput }
		STATUS current
		DESCRIPTION
			"Allows selecting the reference input Trap"
		::= { utg2000c01v1Traps 19 }

		-- 1.3.6.1.4.1.10106.2.1.1.577901.3
		utg2000c01v1ArefFailTrap NOTIFICATION-TYPE
		OBJECTS { trapCounter, utg2000c01v1Index, utg2000c01v1ArefFail }
		STATUS current
		DESCRIPTION
			"Indicates the absence of analog reference Trap"
		::= { utg2000c01v1Traps 413 }

		-- 1.3.6.1.4.1.10106.2.1.1.577901.3
		utg2000c01v1DrefFailTrap NOTIFICATION-TYPE
		OBJECTS { trapCounter, utg2000c01v1Index, utg2000c01v1DrefFail }
		STATUS current
		DESCRIPTION
			"Indicates the absence of digital reference Trap"
		::= { utg2000c01v1Traps 415 }

		-- 1.3.6.1.4.1.10106.2.1.1.577901.3
		utg2000c01v1IrefFailTrap NOTIFICATION-TYPE
		OBJECTS { trapCounter, utg2000c01v1Index, utg2000c01v1IrefFail }
		STATUS current
		DESCRIPTION
			"Indicates the absence of internal reference Trap"
		::= { utg2000c01v1Traps 417 }

		-- 1.3.6.1.4.1.10106.2.1.1.577901.3
		utg2000c01v1RefIncFailTrap NOTIFICATION-TYPE
		OBJECTS { trapCounter, utg2000c01v1Index, utg2000c01v1RefIncFail }
		STATUS current
		DESCRIPTION
			"Indicates that the format of the received reference is different from expected Trap"
		::= { utg2000c01v1Traps 419 }

		-- 1.3.6.1.4.1.10106.2.1.1.577901.3
		utg2000c01v1RefLockFailTrap NOTIFICATION-TYPE
		OBJECTS { trapCounter, utg2000c01v1Index, utg2000c01v1RefLockFail }
		STATUS current
		DESCRIPTION
			"Indicates that the module is not locked to the reference Trap"
		::= { utg2000c01v1Traps 421 }

		-- 1.3.6.1.4.1.10106.2.1.1.577901.3
		utg2000c01v1DrefCrcFailTrap NOTIFICATION-TYPE
		OBJECTS { trapCounter, utg2000c01v1Index, utg2000c01v1DrefCrcFail }
		STATUS current
		DESCRIPTION
			"Indicates that the digital reference has CRC/EDH errors Trap"
		::= { utg2000c01v1Traps 423 }

		-- 1.3.6.1.4.1.10106.2.1.1.577901.3
		utg2000c01v1ArefFormatTrap NOTIFICATION-TYPE
		OBJECTS { trapCounter, utg2000c01v1Index, utg2000c01v1ArefFormat }
		STATUS current
		DESCRIPTION
			"Indicates the detected format of the analog reference Trap"
		::= { utg2000c01v1Traps 429 }

		-- 1.3.6.1.4.1.10106.2.1.1.577901.3
		utg2000c01v1DrefFormatTrap NOTIFICATION-TYPE
		OBJECTS { trapCounter, utg2000c01v1Index, utg2000c01v1DrefFormat }
		STATUS current
		DESCRIPTION
			"Indicates the detected format of the digital reference Trap"
		::= { utg2000c01v1Traps 431 }

		-- 1.3.6.1.4.1.10106.2.1.1.579101
		hvd2002c01v1Traps OBJECT IDENTIFIER ::= { albalaTraps 579101 }

		-- 1.3.6.1.4.1.10106.2.1.1.579101.3
		hvd2002c01v1NoSigTrap NOTIFICATION-TYPE
		OBJECTS { trapCounter, hvd2002c01v1Index, hvd2002c01v1NoSig }
		STATUS current
		DESCRIPTION
			"Input signal status Trap"
		::= { hvd2002c01v1Traps 9 }

		-- 1.3.6.1.4.1.10106.2.1.1.579101.3
		hvd2002c01v1UnlockTrap NOTIFICATION-TYPE
		OBJECTS { trapCounter, hvd2002c01v1Index, hvd2002c01v1Unlock }
		STATUS current
		DESCRIPTION
			"Indicates signal unlock fail Trap"
		::= { hvd2002c01v1Traps 11 }

		-- 1.3.6.1.4.1.10106.2.1.1.583701
		hfs2001c01v1Traps OBJECT IDENTIFIER ::= { albalaTraps 583701 }

		-- 1.3.6.1.4.1.10106.2.1.1.583701.3
		hfs2001c01v1NoSigTrap NOTIFICATION-TYPE
		OBJECTS { trapCounter, hfs2001c01v1Index, hfs2001c01v1NoSig }
		STATUS current
		DESCRIPTION
			"Indicates SDI signal fail Trap"
		::= { hfs2001c01v1Traps 19 }

		-- 1.3.6.1.4.1.10106.2.1.1.583701.3
		hfs2001c01v1UnlockTrap NOTIFICATION-TYPE
		OBJECTS { trapCounter, hfs2001c01v1Index, hfs2001c01v1Unlock }
		STATUS current
		DESCRIPTION
			"Indicates signal unlock Trap"
		::= { hfs2001c01v1Traps 21 }

		-- 1.3.6.1.4.1.10106.2.1.1.583701.3
		hfs2001c01v1EdhCrcTrap NOTIFICATION-TYPE
		OBJECTS { trapCounter, hfs2001c01v1Index, hfs2001c01v1EdhCrc }
		STATUS current
		DESCRIPTION
			"Indicates presence of EDH/CRC errors Trap"
		::= { hfs2001c01v1Traps 23 }

		-- 1.3.6.1.4.1.10106.2.1.1.583701.3
		hfs2001c01v1NoRefTrap NOTIFICATION-TYPE
		OBJECTS { trapCounter, hfs2001c01v1Index, hfs2001c01v1NoRef }
		STATUS current
		DESCRIPTION
			"Indicates reference signal fail Trap"
		::= { hfs2001c01v1Traps 25 }

		-- 1.3.6.1.4.1.10106.2.1.1.583701.3
		hfs2001c01v1RefUnlockTrap NOTIFICATION-TYPE
		OBJECTS { trapCounter, hfs2001c01v1Index, hfs2001c01v1RefUnlock }
		STATUS current
		DESCRIPTION
			"Indicates reference signal unlock fail Trap"
		::= { hfs2001c01v1Traps 27 }

		-- 1.3.6.1.4.1.10106.2.1.1.586701
		gps3003c01v1Traps OBJECT IDENTIFIER ::= { albalaTraps 586701 }

		-- 1.3.6.1.4.1.10106.2.1.1.586701.3
		gps3003c01v1GnssLosTrap NOTIFICATION-TYPE
		OBJECTS { trapCounter, gps3003c01v1Index, gps3003c01v1GnssLos }
		STATUS current
		DESCRIPTION
			"GNSS loss of signal. To be cleared it has to be for 30 s in in 3D-FIX or Time mode Trap"
		::= { gps3003c01v1Traps 75 }

		-- 1.3.6.1.4.1.10106.2.1.1.586701.3
		gps3003c01v1GnssPpsLosTrap NOTIFICATION-TYPE
		OBJECTS { trapCounter, gps3003c01v1Index, gps3003c01v1GnssPpsLos }
		STATUS current
		DESCRIPTION
			"GNSS loss of PPS. It is cleared when the error of the PPS delivered by GNSS module is less than 5 ns. It is set when the delay is greater than 50 ns Trap"
		::= { gps3003c01v1Traps 77 }

		-- 1.3.6.1.4.1.10106.2.1.1.586701.3
		gps3003c01v1GnssUnlockTrap NOTIFICATION-TYPE
		OBJECTS { trapCounter, gps3003c01v1Index, gps3003c01v1GnssUnlock }
		STATUS current
		DESCRIPTION
			"GNSS PPS unlock. It is cleared when the error of the output PPS is less than 10 ns. It is set when the error is greater than 100 ns. Trap"
		::= { gps3003c01v1Traps 79 }

		-- 1.3.6.1.4.1.10106.2.1.1.586701.3
		gps3003c01v1GnssPpsErrTrap NOTIFICATION-TYPE
		OBJECTS { trapCounter, gps3003c01v1Index, gps3003c01v1GnssPpsErr }
		STATUS current
		DESCRIPTION
			"GNSS pulse error. It is cleared when the error of the output PPS is less than the value specified in 'GNSS valid PPS margin'. It is set when the error is greater than this value. Trap"
		::= { gps3003c01v1Traps 81 }

		-- 1.3.6.1.4.1.10106.2.1.1.586701.3
		gps3003c01v1PtpLosTrap NOTIFICATION-TYPE
		OBJECTS { trapCounter, gps3003c01v1Index, gps3003c01v1PtpLos }
		STATUS current
		DESCRIPTION
			"PTP loss of signal.It is cleared when the PTP module is in Slave or Uncalibrated mode Trap"
		::= { gps3003c01v1Traps 83 }

		-- 1.3.6.1.4.1.10106.2.1.1.586701.3
		gps3003c01v1PtpPpsLosTrap NOTIFICATION-TYPE
		OBJECTS { trapCounter, gps3003c01v1Index, gps3003c01v1PtpPpsLos }
		STATUS current
		DESCRIPTION
			"PTP loss of PPS. It is cleared after 30 s receiving a valid PPS from PTP module Trap"
		::= { gps3003c01v1Traps 85 }

		-- 1.3.6.1.4.1.10106.2.1.1.586701.3
		gps3003c01v1PtpUnlockTrap NOTIFICATION-TYPE
		OBJECTS { trapCounter, gps3003c01v1Index, gps3003c01v1PtpUnlock }
		STATUS current
		DESCRIPTION
			"PTP PPS unlock. It is cleared when the error of the output PPS is less than 25 ns. It is set when the error is greater than 250 ns. Trap"
		::= { gps3003c01v1Traps 87 }

		-- 1.3.6.1.4.1.10106.2.1.1.586701.3
		gps3003c01v1PtpPpsErrTrap NOTIFICATION-TYPE
		OBJECTS { trapCounter, gps3003c01v1Index, gps3003c01v1PtpPpsErr }
		STATUS current
		DESCRIPTION
			"PTP PPS error. It is cleared when the error of the output PPS is less than the value specified in 'PTP valid PPS margin'. It is set when the error is greater than this value. Trap"
		::= { gps3003c01v1Traps 89 }

		-- 1.3.6.1.4.1.10106.2.1.1.586701.3
		gps3003c01v1SyncStateTrap NOTIFICATION-TYPE
		OBJECTS { trapCounter, gps3003c01v1Index, gps3003c01v1SyncState }
		STATUS current
		DESCRIPTION
			"Indicates the synchronization state Trap"
		::= { gps3003c01v1Traps 91 }

		-- 1.3.6.1.4.1.10106.2.1.1.586701.3
		gps3003c01v1ValidPpsTrap NOTIFICATION-TYPE
		OBJECTS { trapCounter, gps3003c01v1Index, gps3003c01v1ValidPps }
		STATUS current
		DESCRIPTION
			"Indicates that the internally generated PPS signal has been phase aligned with an external reference (GNSS or PTP) Trap"
		::= { gps3003c01v1Traps 93 }

		-- 1.3.6.1.4.1.10106.2.1.1.586701.3
		gps3003c01v1ModuleActiveTrap NOTIFICATION-TYPE
		OBJECTS { trapCounter, gps3003c01v1Index, gps3003c01v1ModuleActive }
		STATUS current
		DESCRIPTION
			"Indicates that this module is the one that provides the reference signals Trap"
		::= { gps3003c01v1Traps 95 }

		-- 1.3.6.1.4.1.10106.2.1.1.586701.3
		gps3003c01v1RedSyncStateTrap NOTIFICATION-TYPE
		OBJECTS { trapCounter, gps3003c01v1Index, gps3003c01v1RedSyncState }
		STATUS current
		DESCRIPTION
			"Indicates the redundant module's synchronization state Trap"
		::= { gps3003c01v1Traps 97 }

		-- 1.3.6.1.4.1.10106.2.1.1.586701.3
		gps3003c01v1RedModuleTrap NOTIFICATION-TYPE
		OBJECTS { trapCounter, gps3003c01v1Index, gps3003c01v1RedModule }
		STATUS current
		DESCRIPTION
			"Indicates if the redundant module is present Trap"
		::= { gps3003c01v1Traps 99 }

		-- 1.3.6.1.4.1.10106.2.1.1.586701.3
		gps3003c01v1FixModeTrap NOTIFICATION-TYPE
		OBJECTS { trapCounter, gps3003c01v1Index, gps3003c01v1FixMode }
		STATUS current
		DESCRIPTION
			"GNSS receiver module satellite tracking mode Trap"
		::= { gps3003c01v1Traps 101 }

		-- 1.3.6.1.4.1.10106.2.1.1.586701.3
		gps3003c01v1PowerStatTrap NOTIFICATION-TYPE
		OBJECTS { trapCounter, gps3003c01v1Index, gps3003c01v1PowerStat }
		STATUS current
		DESCRIPTION
			"Indicates the power supply status Trap"
		::= { gps3003c01v1Traps 117 }

		-- 1.3.6.1.4.1.10106.2.1.1.586701.3
		gps3003c01v1AntennaStatTrap NOTIFICATION-TYPE
		OBJECTS { trapCounter, gps3003c01v1Index, gps3003c01v1AntennaStat }
		STATUS current
		DESCRIPTION
			"Indicates the antenna connection status Trap"
		::= { gps3003c01v1Traps 119 }

		-- 1.3.6.1.4.1.10106.2.1.1.586701.3
		gps3003c01v1EthLinkTrap NOTIFICATION-TYPE
		OBJECTS { trapCounter, gps3003c01v1Index, gps3003c01v1EthLink }
		STATUS current
		DESCRIPTION
			"Indicates that the Ethernet link is OK Trap"
		::= { gps3003c01v1Traps 121 }

		-- 1.3.6.1.4.1.10106.2.1.1.586701.3
		gps3003c01v1OnePpsStatTrap NOTIFICATION-TYPE
		OBJECTS { trapCounter, gps3003c01v1Index, gps3003c01v1OnePpsStat }
		STATUS current
		DESCRIPTION
			"Indicates that the module is delivering a valid PPS Trap"
		::= { gps3003c01v1Traps 127 }

		-- 1.3.6.1.4.1.10106.2.1.1.586801
		sem2000c01v1Traps OBJECT IDENTIFIER ::= { albalaTraps 586801 }

		-- 1.3.6.1.4.1.10106.2.1.1.586801.3
		sem2000c01v1SfpPresTrap NOTIFICATION-TYPE
		OBJECTS { trapCounter, sem2000c01v1Index, sem2000c01v1SfpPres }
		STATUS current
		DESCRIPTION
			"SFP module present Trap"
		::= { sem2000c01v1Traps 11 }

		-- 1.3.6.1.4.1.10106.2.1.1.586801.3
		sem2000c01v1SfpFailTrap NOTIFICATION-TYPE
		OBJECTS { trapCounter, sem2000c01v1Index, sem2000c01v1SfpFail }
		STATUS current
		DESCRIPTION
			"Indicates a laser fault Trap"
		::= { sem2000c01v1Traps 13 }

		-- 1.3.6.1.4.1.10106.2.1.1.586801.3
		sem2000c01v1SfpLosTrap NOTIFICATION-TYPE
		OBJECTS { trapCounter, sem2000c01v1Index, sem2000c01v1SfpLos }
		STATUS current
		DESCRIPTION
			"SFP loss of signal Trap"
		::= { sem2000c01v1Traps 15 }

		-- 1.3.6.1.4.1.10106.2.1.1.586801.3
		sem2000c01v1P1StatusTrap NOTIFICATION-TYPE
		OBJECTS { trapCounter, sem2000c01v1Index, sem2000c01v1P1Status }
		STATUS current
		DESCRIPTION
			"Ethernet connection status in Port 1 Trap"
		::= { sem2000c01v1Traps 19 }

		-- 1.3.6.1.4.1.10106.2.1.1.586801.3
		sem2000c01v1P2StatusTrap NOTIFICATION-TYPE
		OBJECTS { trapCounter, sem2000c01v1Index, sem2000c01v1P2Status }
		STATUS current
		DESCRIPTION
			"Ethernet connection status in Port 2 Trap"
		::= { sem2000c01v1Traps 21 }

		-- 1.3.6.1.4.1.10106.2.1.1.586801.3
		sem2000c01v1PoStatusTrap NOTIFICATION-TYPE
		OBJECTS { trapCounter, sem2000c01v1Index, sem2000c01v1PoStatus }
		STATUS current
		DESCRIPTION
			"Ethernet connection status in Optical Port Trap"
		::= { sem2000c01v1Traps 23 }

		-- 1.3.6.1.4.1.10106.2.1.1.586801.3
		sem2000c01v1BusUnlockTrap NOTIFICATION-TYPE
		OBJECTS { trapCounter, sem2000c01v1Index, sem2000c01v1BusUnlock }
		STATUS current
		DESCRIPTION
			"Module not locked to the 10 MHz signal from bus Trap"
		::= { sem2000c01v1Traps 29 }

		-- 1.3.6.1.4.1.10106.2.1.1.586801.3
		sem2000c01v1BusLosTrap NOTIFICATION-TYPE
		OBJECTS { trapCounter, sem2000c01v1Index, sem2000c01v1BusLos }
		STATUS current
		DESCRIPTION
			"10 MHz signal not detected in bus Trap"
		::= { sem2000c01v1Traps 31 }

		-- 1.3.6.1.4.1.10106.2.1.1.587301
		gps3003c02v1Traps OBJECT IDENTIFIER ::= { albalaTraps 587301 }

		-- 1.3.6.1.4.1.10106.2.1.1.587301.3
		gps3003c02v1GnssLosTrap NOTIFICATION-TYPE
		OBJECTS { trapCounter, gps3003c02v1Index, gps3003c02v1GnssLos }
		STATUS current
		DESCRIPTION
			"GNSS loss of signal. To be cleared it has to be for 30 s in in 3D-FIX or Time mode Trap"
		::= { gps3003c02v1Traps 75 }

		-- 1.3.6.1.4.1.10106.2.1.1.587301.3
		gps3003c02v1GnssPpsLosTrap NOTIFICATION-TYPE
		OBJECTS { trapCounter, gps3003c02v1Index, gps3003c02v1GnssPpsLos }
		STATUS current
		DESCRIPTION
			"GNSS loss of PPS. It is cleared when the error of the PPS delivered by GNSS module is less than 5 ns. It is set when the delay is greater than 50 ns Trap"
		::= { gps3003c02v1Traps 77 }

		-- 1.3.6.1.4.1.10106.2.1.1.587301.3
		gps3003c02v1GnssUnlockTrap NOTIFICATION-TYPE
		OBJECTS { trapCounter, gps3003c02v1Index, gps3003c02v1GnssUnlock }
		STATUS current
		DESCRIPTION
			"GNSS PPS unlock. It is cleared when the error of the output PPS is less than 10 ns. It is set when the error is greater than 100 ns. Trap"
		::= { gps3003c02v1Traps 79 }

		-- 1.3.6.1.4.1.10106.2.1.1.587301.3
		gps3003c02v1GnssPpsErrTrap NOTIFICATION-TYPE
		OBJECTS { trapCounter, gps3003c02v1Index, gps3003c02v1GnssPpsErr }
		STATUS current
		DESCRIPTION
			"GNSS pulse error. It is cleared when the error of the output PPS is less than the value specified in 'GNSS valid PPS margin'. It is set when the error is greater than this value. Trap"
		::= { gps3003c02v1Traps 81 }

		-- 1.3.6.1.4.1.10106.2.1.1.587301.3
		gps3003c02v1PtpLosTrap NOTIFICATION-TYPE
		OBJECTS { trapCounter, gps3003c02v1Index, gps3003c02v1PtpLos }
		STATUS current
		DESCRIPTION
			"PTP loss of signal.It is cleared when the PTP module is in Slave or Uncalibrated mode Trap"
		::= { gps3003c02v1Traps 83 }

		-- 1.3.6.1.4.1.10106.2.1.1.587301.3
		gps3003c02v1PtpPpsLosTrap NOTIFICATION-TYPE
		OBJECTS { trapCounter, gps3003c02v1Index, gps3003c02v1PtpPpsLos }
		STATUS current
		DESCRIPTION
			"PTP loss of PPS. It is cleared after 30 s receiving a valid PPS from PTP module Trap"
		::= { gps3003c02v1Traps 85 }

		-- 1.3.6.1.4.1.10106.2.1.1.587301.3
		gps3003c02v1PtpUnlockTrap NOTIFICATION-TYPE
		OBJECTS { trapCounter, gps3003c02v1Index, gps3003c02v1PtpUnlock }
		STATUS current
		DESCRIPTION
			"PTP PPS unlock. It is cleared when the error of the output PPS is less than 25 ns. It is set when the error is greater than 250 ns. Trap"
		::= { gps3003c02v1Traps 87 }

		-- 1.3.6.1.4.1.10106.2.1.1.587301.3
		gps3003c02v1PtpPpsErrTrap NOTIFICATION-TYPE
		OBJECTS { trapCounter, gps3003c02v1Index, gps3003c02v1PtpPpsErr }
		STATUS current
		DESCRIPTION
			"PTP PPS error. It is cleared when the error of the output PPS is less than the value specified in 'PTP valid PPS margin'. It is set when the error is greater than this value. Trap"
		::= { gps3003c02v1Traps 89 }

		-- 1.3.6.1.4.1.10106.2.1.1.587301.3
		gps3003c02v1SyncStateTrap NOTIFICATION-TYPE
		OBJECTS { trapCounter, gps3003c02v1Index, gps3003c02v1SyncState }
		STATUS current
		DESCRIPTION
			"Indicates the synchronization state Trap"
		::= { gps3003c02v1Traps 91 }

		-- 1.3.6.1.4.1.10106.2.1.1.587301.3
		gps3003c02v1ValidPpsTrap NOTIFICATION-TYPE
		OBJECTS { trapCounter, gps3003c02v1Index, gps3003c02v1ValidPps }
		STATUS current
		DESCRIPTION
			"Indicates that the internally generated PPS signal has been phase aligned with an external reference (GNSS or PTP) Trap"
		::= { gps3003c02v1Traps 93 }

		-- 1.3.6.1.4.1.10106.2.1.1.587301.3
		gps3003c02v1ModuleActiveTrap NOTIFICATION-TYPE
		OBJECTS { trapCounter, gps3003c02v1Index, gps3003c02v1ModuleActive }
		STATUS current
		DESCRIPTION
			"Indicates that this module is the one that provides the reference signals Trap"
		::= { gps3003c02v1Traps 95 }

		-- 1.3.6.1.4.1.10106.2.1.1.587301.3
		gps3003c02v1RedSyncStateTrap NOTIFICATION-TYPE
		OBJECTS { trapCounter, gps3003c02v1Index, gps3003c02v1RedSyncState }
		STATUS current
		DESCRIPTION
			"Indicates the redundant module's synchronization state Trap"
		::= { gps3003c02v1Traps 97 }

		-- 1.3.6.1.4.1.10106.2.1.1.587301.3
		gps3003c02v1RedModuleTrap NOTIFICATION-TYPE
		OBJECTS { trapCounter, gps3003c02v1Index, gps3003c02v1RedModule }
		STATUS current
		DESCRIPTION
			"Indicates if the redundant module is present Trap"
		::= { gps3003c02v1Traps 99 }

		-- 1.3.6.1.4.1.10106.2.1.1.587301.3
		gps3003c02v1FixModeTrap NOTIFICATION-TYPE
		OBJECTS { trapCounter, gps3003c02v1Index, gps3003c02v1FixMode }
		STATUS current
		DESCRIPTION
			"GNSS receiver module satellite tracking mode Trap"
		::= { gps3003c02v1Traps 101 }

		-- 1.3.6.1.4.1.10106.2.1.1.587301.3
		gps3003c02v1PowerStatTrap NOTIFICATION-TYPE
		OBJECTS { trapCounter, gps3003c02v1Index, gps3003c02v1PowerStat }
		STATUS current
		DESCRIPTION
			"Indicates the power supply status Trap"
		::= { gps3003c02v1Traps 117 }

		-- 1.3.6.1.4.1.10106.2.1.1.587301.3
		gps3003c02v1AntennaStatTrap NOTIFICATION-TYPE
		OBJECTS { trapCounter, gps3003c02v1Index, gps3003c02v1AntennaStat }
		STATUS current
		DESCRIPTION
			"Indicates the antenna connection status Trap"
		::= { gps3003c02v1Traps 119 }

		-- 1.3.6.1.4.1.10106.2.1.1.587301.3
		gps3003c02v1EthLinkTrap NOTIFICATION-TYPE
		OBJECTS { trapCounter, gps3003c02v1Index, gps3003c02v1EthLink }
		STATUS current
		DESCRIPTION
			"Indicates that the Ethernet link is OK Trap"
		::= { gps3003c02v1Traps 121 }

		-- 1.3.6.1.4.1.10106.2.1.1.587301.3
		gps3003c02v1OnePpsStatTrap NOTIFICATION-TYPE
		OBJECTS { trapCounter, gps3003c02v1Index, gps3003c02v1OnePpsStat }
		STATUS current
		DESCRIPTION
			"Indicates that the module is delivering a valid PPS Trap"
		::= { gps3003c02v1Traps 127 }

		-- 1.3.6.1.4.1.10106.2.1.1.587501
		gps3003c03v1Traps OBJECT IDENTIFIER ::= { albalaTraps 587501 }

		-- 1.3.6.1.4.1.10106.2.1.1.587501.3
		gps3003c03v1GnssLosTrap NOTIFICATION-TYPE
		OBJECTS { trapCounter, gps3003c03v1Index, gps3003c03v1GnssLos }
		STATUS current
		DESCRIPTION
			"GNSS loss of signal. To be cleared it has to be for 30 s in in 3D-FIX or Time mode Trap"
		::= { gps3003c03v1Traps 75 }

		-- 1.3.6.1.4.1.10106.2.1.1.587501.3
		gps3003c03v1GnssPpsLosTrap NOTIFICATION-TYPE
		OBJECTS { trapCounter, gps3003c03v1Index, gps3003c03v1GnssPpsLos }
		STATUS current
		DESCRIPTION
			"GNSS loss of PPS. It is cleared when the error of the PPS delivered by GNSS module is less than 5 ns. It is set when the delay is greater than 50 ns Trap"
		::= { gps3003c03v1Traps 77 }

		-- 1.3.6.1.4.1.10106.2.1.1.587501.3
		gps3003c03v1GnssUnlockTrap NOTIFICATION-TYPE
		OBJECTS { trapCounter, gps3003c03v1Index, gps3003c03v1GnssUnlock }
		STATUS current
		DESCRIPTION
			"GNSS PPS unlock. It is cleared when the error of the output PPS is less than 10 ns. It is set when the error is greater than 100 ns. Trap"
		::= { gps3003c03v1Traps 79 }

		-- 1.3.6.1.4.1.10106.2.1.1.587501.3
		gps3003c03v1GnssPpsErrTrap NOTIFICATION-TYPE
		OBJECTS { trapCounter, gps3003c03v1Index, gps3003c03v1GnssPpsErr }
		STATUS current
		DESCRIPTION
			"GNSS pulse error. It is cleared when the error of the output PPS is less than the value specified in 'GNSS valid PPS margin'. It is set when the error is greater than this value. Trap"
		::= { gps3003c03v1Traps 81 }

		-- 1.3.6.1.4.1.10106.2.1.1.587501.3
		gps3003c03v1PtpLosTrap NOTIFICATION-TYPE
		OBJECTS { trapCounter, gps3003c03v1Index, gps3003c03v1PtpLos }
		STATUS current
		DESCRIPTION
			"PTP loss of signal.It is cleared when the PTP module is in Slave or Uncalibrated mode Trap"
		::= { gps3003c03v1Traps 83 }

		-- 1.3.6.1.4.1.10106.2.1.1.587501.3
		gps3003c03v1PtpPpsLosTrap NOTIFICATION-TYPE
		OBJECTS { trapCounter, gps3003c03v1Index, gps3003c03v1PtpPpsLos }
		STATUS current
		DESCRIPTION
			"PTP loss of PPS. It is cleared after 30 s receiving a valid PPS from PTP module Trap"
		::= { gps3003c03v1Traps 85 }

		-- 1.3.6.1.4.1.10106.2.1.1.587501.3
		gps3003c03v1PtpUnlockTrap NOTIFICATION-TYPE
		OBJECTS { trapCounter, gps3003c03v1Index, gps3003c03v1PtpUnlock }
		STATUS current
		DESCRIPTION
			"PTP PPS unlock. It is cleared when the error of the output PPS is less than 25 ns. It is set when the error is greater than 250 ns. Trap"
		::= { gps3003c03v1Traps 87 }

		-- 1.3.6.1.4.1.10106.2.1.1.587501.3
		gps3003c03v1PtpPpsErrTrap NOTIFICATION-TYPE
		OBJECTS { trapCounter, gps3003c03v1Index, gps3003c03v1PtpPpsErr }
		STATUS current
		DESCRIPTION
			"PTP PPS error. It is cleared when the error of the output PPS is less than the value specified in 'PTP valid PPS margin'. It is set when the error is greater than this value. Trap"
		::= { gps3003c03v1Traps 89 }

		-- 1.3.6.1.4.1.10106.2.1.1.587501.3
		gps3003c03v1SyncStateTrap NOTIFICATION-TYPE
		OBJECTS { trapCounter, gps3003c03v1Index, gps3003c03v1SyncState }
		STATUS current
		DESCRIPTION
			"Indicates the synchronization state Trap"
		::= { gps3003c03v1Traps 91 }

		-- 1.3.6.1.4.1.10106.2.1.1.587501.3
		gps3003c03v1ValidPpsTrap NOTIFICATION-TYPE
		OBJECTS { trapCounter, gps3003c03v1Index, gps3003c03v1ValidPps }
		STATUS current
		DESCRIPTION
			"Indicates that the internally generated PPS signal has been phase aligned with an external reference (GNSS or PTP) Trap"
		::= { gps3003c03v1Traps 93 }

		-- 1.3.6.1.4.1.10106.2.1.1.587501.3
		gps3003c03v1ModuleActiveTrap NOTIFICATION-TYPE
		OBJECTS { trapCounter, gps3003c03v1Index, gps3003c03v1ModuleActive }
		STATUS current
		DESCRIPTION
			"Indicates that this module is the one that provides the reference signals Trap"
		::= { gps3003c03v1Traps 95 }

		-- 1.3.6.1.4.1.10106.2.1.1.587501.3
		gps3003c03v1RedSyncStateTrap NOTIFICATION-TYPE
		OBJECTS { trapCounter, gps3003c03v1Index, gps3003c03v1RedSyncState }
		STATUS current
		DESCRIPTION
			"Indicates the redundant module's synchronization state Trap"
		::= { gps3003c03v1Traps 97 }

		-- 1.3.6.1.4.1.10106.2.1.1.587501.3
		gps3003c03v1RedModuleTrap NOTIFICATION-TYPE
		OBJECTS { trapCounter, gps3003c03v1Index, gps3003c03v1RedModule }
		STATUS current
		DESCRIPTION
			"Indicates if the redundant module is present Trap"
		::= { gps3003c03v1Traps 99 }

		-- 1.3.6.1.4.1.10106.2.1.1.587501.3
		gps3003c03v1FixModeTrap NOTIFICATION-TYPE
		OBJECTS { trapCounter, gps3003c03v1Index, gps3003c03v1FixMode }
		STATUS current
		DESCRIPTION
			"GNSS receiver module satellite tracking mode Trap"
		::= { gps3003c03v1Traps 101 }

		-- 1.3.6.1.4.1.10106.2.1.1.587501.3
		gps3003c03v1PowerStatTrap NOTIFICATION-TYPE
		OBJECTS { trapCounter, gps3003c03v1Index, gps3003c03v1PowerStat }
		STATUS current
		DESCRIPTION
			"Indicates the power supply status Trap"
		::= { gps3003c03v1Traps 117 }

		-- 1.3.6.1.4.1.10106.2.1.1.587501.3
		gps3003c03v1AntennaStatTrap NOTIFICATION-TYPE
		OBJECTS { trapCounter, gps3003c03v1Index, gps3003c03v1AntennaStat }
		STATUS current
		DESCRIPTION
			"Indicates the antenna connection status Trap"
		::= { gps3003c03v1Traps 119 }

		-- 1.3.6.1.4.1.10106.2.1.1.587501.3
		gps3003c03v1EthLinkTrap NOTIFICATION-TYPE
		OBJECTS { trapCounter, gps3003c03v1Index, gps3003c03v1EthLink }
		STATUS current
		DESCRIPTION
			"Indicates that the Ethernet link is OK Trap"
		::= { gps3003c03v1Traps 121 }

		-- 1.3.6.1.4.1.10106.2.1.1.587501.3
		gps3003c03v1OnePpsStatTrap NOTIFICATION-TYPE
		OBJECTS { trapCounter, gps3003c03v1Index, gps3003c03v1OnePpsStat }
		STATUS current
		DESCRIPTION
			"Indicates that the module is delivering a valid PPS Trap"
		::= { gps3003c03v1Traps 127 }

		-- 1.3.6.1.4.1.10106.2.1.1.587701
		gps3003c04v1Traps OBJECT IDENTIFIER ::= { albalaTraps 587701 }

		-- 1.3.6.1.4.1.10106.2.1.1.587701.3
		gps3003c04v1GnssLosTrap NOTIFICATION-TYPE
		OBJECTS { trapCounter, gps3003c04v1Index, gps3003c04v1GnssLos }
		STATUS current
		DESCRIPTION
			"GNSS loss of signal. To be cleared it has to be for 30 s in in 3D-FIX or Time mode Trap"
		::= { gps3003c04v1Traps 75 }

		-- 1.3.6.1.4.1.10106.2.1.1.587701.3
		gps3003c04v1GnssPpsLosTrap NOTIFICATION-TYPE
		OBJECTS { trapCounter, gps3003c04v1Index, gps3003c04v1GnssPpsLos }
		STATUS current
		DESCRIPTION
			"GNSS loss of PPS. It is cleared when the error of the PPS delivered by GNSS module is less than 5 ns. It is set when the delay is greater than 50 ns Trap"
		::= { gps3003c04v1Traps 77 }

		-- 1.3.6.1.4.1.10106.2.1.1.587701.3
		gps3003c04v1GnssUnlockTrap NOTIFICATION-TYPE
		OBJECTS { trapCounter, gps3003c04v1Index, gps3003c04v1GnssUnlock }
		STATUS current
		DESCRIPTION
			"GNSS PPS unlock. It is cleared when the error of the output PPS is less than 10 ns. It is set when the error is greater than 100 ns. Trap"
		::= { gps3003c04v1Traps 79 }

		-- 1.3.6.1.4.1.10106.2.1.1.587701.3
		gps3003c04v1GnssPpsErrTrap NOTIFICATION-TYPE
		OBJECTS { trapCounter, gps3003c04v1Index, gps3003c04v1GnssPpsErr }
		STATUS current
		DESCRIPTION
			"GNSS pulse error. It is cleared when the error of the output PPS is less than the value specified in 'GNSS valid PPS margin'. It is set when the error is greater than this value. Trap"
		::= { gps3003c04v1Traps 81 }

		-- 1.3.6.1.4.1.10106.2.1.1.587701.3
		gps3003c04v1PtpLosTrap NOTIFICATION-TYPE
		OBJECTS { trapCounter, gps3003c04v1Index, gps3003c04v1PtpLos }
		STATUS current
		DESCRIPTION
			"PTP loss of signal.It is cleared when the PTP module is in Slave or Uncalibrated mode Trap"
		::= { gps3003c04v1Traps 83 }

		-- 1.3.6.1.4.1.10106.2.1.1.587701.3
		gps3003c04v1PtpPpsLosTrap NOTIFICATION-TYPE
		OBJECTS { trapCounter, gps3003c04v1Index, gps3003c04v1PtpPpsLos }
		STATUS current
		DESCRIPTION
			"PTP loss of PPS. It is cleared after 30 s receiving a valid PPS from PTP module Trap"
		::= { gps3003c04v1Traps 85 }

		-- 1.3.6.1.4.1.10106.2.1.1.587701.3
		gps3003c04v1PtpUnlockTrap NOTIFICATION-TYPE
		OBJECTS { trapCounter, gps3003c04v1Index, gps3003c04v1PtpUnlock }
		STATUS current
		DESCRIPTION
			"PTP PPS unlock. It is cleared when the error of the output PPS is less than 25 ns. It is set when the error is greater than 250 ns. Trap"
		::= { gps3003c04v1Traps 87 }

		-- 1.3.6.1.4.1.10106.2.1.1.587701.3
		gps3003c04v1PtpPpsErrTrap NOTIFICATION-TYPE
		OBJECTS { trapCounter, gps3003c04v1Index, gps3003c04v1PtpPpsErr }
		STATUS current
		DESCRIPTION
			"PTP PPS error. It is cleared when the error of the output PPS is less than the value specified in 'PTP valid PPS margin'. It is set when the error is greater than this value. Trap"
		::= { gps3003c04v1Traps 89 }

		-- 1.3.6.1.4.1.10106.2.1.1.587701.3
		gps3003c04v1SyncStateTrap NOTIFICATION-TYPE
		OBJECTS { trapCounter, gps3003c04v1Index, gps3003c04v1SyncState }
		STATUS current
		DESCRIPTION
			"Indicates the synchronization state Trap"
		::= { gps3003c04v1Traps 91 }

		-- 1.3.6.1.4.1.10106.2.1.1.587701.3
		gps3003c04v1ValidPpsTrap NOTIFICATION-TYPE
		OBJECTS { trapCounter, gps3003c04v1Index, gps3003c04v1ValidPps }
		STATUS current
		DESCRIPTION
			"Indicates that the internally generated PPS signal has been phase aligned with an external reference (GNSS or PTP) Trap"
		::= { gps3003c04v1Traps 93 }

		-- 1.3.6.1.4.1.10106.2.1.1.587701.3
		gps3003c04v1ModuleActiveTrap NOTIFICATION-TYPE
		OBJECTS { trapCounter, gps3003c04v1Index, gps3003c04v1ModuleActive }
		STATUS current
		DESCRIPTION
			"Indicates that this module is the one that provides the reference signals Trap"
		::= { gps3003c04v1Traps 95 }

		-- 1.3.6.1.4.1.10106.2.1.1.587701.3
		gps3003c04v1RedSyncStateTrap NOTIFICATION-TYPE
		OBJECTS { trapCounter, gps3003c04v1Index, gps3003c04v1RedSyncState }
		STATUS current
		DESCRIPTION
			"Indicates the redundant module's synchronization state Trap"
		::= { gps3003c04v1Traps 97 }

		-- 1.3.6.1.4.1.10106.2.1.1.587701.3
		gps3003c04v1RedModuleTrap NOTIFICATION-TYPE
		OBJECTS { trapCounter, gps3003c04v1Index, gps3003c04v1RedModule }
		STATUS current
		DESCRIPTION
			"Indicates if the redundant module is present Trap"
		::= { gps3003c04v1Traps 99 }

		-- 1.3.6.1.4.1.10106.2.1.1.587701.3
		gps3003c04v1FixModeTrap NOTIFICATION-TYPE
		OBJECTS { trapCounter, gps3003c04v1Index, gps3003c04v1FixMode }
		STATUS current
		DESCRIPTION
			"GNSS receiver module satellite tracking mode Trap"
		::= { gps3003c04v1Traps 101 }

		-- 1.3.6.1.4.1.10106.2.1.1.587701.3
		gps3003c04v1PowerStatTrap NOTIFICATION-TYPE
		OBJECTS { trapCounter, gps3003c04v1Index, gps3003c04v1PowerStat }
		STATUS current
		DESCRIPTION
			"Indicates the power supply status Trap"
		::= { gps3003c04v1Traps 117 }

		-- 1.3.6.1.4.1.10106.2.1.1.587701.3
		gps3003c04v1AntennaStatTrap NOTIFICATION-TYPE
		OBJECTS { trapCounter, gps3003c04v1Index, gps3003c04v1AntennaStat }
		STATUS current
		DESCRIPTION
			"Indicates the antenna connection status Trap"
		::= { gps3003c04v1Traps 119 }

		-- 1.3.6.1.4.1.10106.2.1.1.587701.3
		gps3003c04v1EthLinkTrap NOTIFICATION-TYPE
		OBJECTS { trapCounter, gps3003c04v1Index, gps3003c04v1EthLink }
		STATUS current
		DESCRIPTION
			"Indicates that the Ethernet link is OK Trap"
		::= { gps3003c04v1Traps 121 }

		-- 1.3.6.1.4.1.10106.2.1.1.587701.3
		gps3003c04v1OnePpsStatTrap NOTIFICATION-TYPE
		OBJECTS { trapCounter, gps3003c04v1Index, gps3003c04v1OnePpsStat }
		STATUS current
		DESCRIPTION
			"Indicates that the module is delivering a valid PPS Trap"
		::= { gps3003c04v1Traps 127 }

		-- 1.3.6.1.4.1.10106.2.1.1.592801
		ase2008c01v1Traps OBJECT IDENTIFIER ::= { albalaTraps 592801 }

		-- 1.3.6.1.4.1.10106.2.1.1.592801.3
		ase2008c01v1AudChEn1Trap NOTIFICATION-TYPE
		OBJECTS { trapCounter, ase2008c01v1Index, ase2008c01v1AudChEn1 }
		STATUS current
		DESCRIPTION
			"Enable channel 1 Elementary Stream transmission Trap"
		::= { ase2008c01v1Traps 17 }

		-- 1.3.6.1.4.1.10106.2.1.1.592801.3
		ase2008c01v1AudChEn2Trap NOTIFICATION-TYPE
		OBJECTS { trapCounter, ase2008c01v1Index, ase2008c01v1AudChEn2 }
		STATUS current
		DESCRIPTION
			"Enable channel 2 Elementary Stream transmission Trap"
		::= { ase2008c01v1Traps 19 }

		-- 1.3.6.1.4.1.10106.2.1.1.592801.3
		ase2008c01v1AudChEn3Trap NOTIFICATION-TYPE
		OBJECTS { trapCounter, ase2008c01v1Index, ase2008c01v1AudChEn3 }
		STATUS current
		DESCRIPTION
			"Enable channel 3 Elementary Stream transmission Trap"
		::= { ase2008c01v1Traps 21 }

		-- 1.3.6.1.4.1.10106.2.1.1.592801.3
		ase2008c01v1AudChEn4Trap NOTIFICATION-TYPE
		OBJECTS { trapCounter, ase2008c01v1Index, ase2008c01v1AudChEn4 }
		STATUS current
		DESCRIPTION
			"Enable channel 4 Elementary Stream transmission Trap"
		::= { ase2008c01v1Traps 23 }

		-- 1.3.6.1.4.1.10106.2.1.1.592801.3
		ase2008c01v1AudChEn5Trap NOTIFICATION-TYPE
		OBJECTS { trapCounter, ase2008c01v1Index, ase2008c01v1AudChEn5 }
		STATUS current
		DESCRIPTION
			"Enable channel 5 Elementary Stream transmission Trap"
		::= { ase2008c01v1Traps 25 }

		-- 1.3.6.1.4.1.10106.2.1.1.592801.3
		ase2008c01v1AudChEn6Trap NOTIFICATION-TYPE
		OBJECTS { trapCounter, ase2008c01v1Index, ase2008c01v1AudChEn6 }
		STATUS current
		DESCRIPTION
			"Enable channel 6 Elementary Stream transmission Trap"
		::= { ase2008c01v1Traps 27 }

		-- 1.3.6.1.4.1.10106.2.1.1.592801.3
		ase2008c01v1AudChEn7Trap NOTIFICATION-TYPE
		OBJECTS { trapCounter, ase2008c01v1Index, ase2008c01v1AudChEn7 }
		STATUS current
		DESCRIPTION
			"Enable channel 7 Elementary Stream transmission Trap"
		::= { ase2008c01v1Traps 29 }

		-- 1.3.6.1.4.1.10106.2.1.1.592801.3
		ase2008c01v1AudChEn8Trap NOTIFICATION-TYPE
		OBJECTS { trapCounter, ase2008c01v1Index, ase2008c01v1AudChEn8 }
		STATUS current
		DESCRIPTION
			"Enable channel 8 Elementary Stream transmission Trap"
		::= { ase2008c01v1Traps 31 }

		-- 1.3.6.1.4.1.10106.2.1.1.592801.3
		ase2008c01v1AudClipTrap NOTIFICATION-TYPE
		OBJECTS { trapCounter, ase2008c01v1Index, ase2008c01v1AudClip }
		STATUS current
		DESCRIPTION
			"Indicates clipping (due to either excessive levels at the analogue input or excessive applied gain during digital processing) Trap"
		::= { ase2008c01v1Traps 35 }

		-- 1.3.6.1.4.1.10106.2.1.1.592901
		aip2000c01v1Traps OBJECT IDENTIFIER ::= { albalaTraps 592901 }

		-- 1.3.6.1.4.1.10106.2.1.1.592901.3
		aip2000c01v1StreamOk1Trap NOTIFICATION-TYPE
		OBJECTS { trapCounter, aip2000c01v1Index, aip2000c01v1StreamOk1 }
		STATUS current
		DESCRIPTION
			"AES67 RX1 stream received Trap"
		::= { aip2000c01v1Traps 111 }

		-- 1.3.6.1.4.1.10106.2.1.1.592901.3
		aip2000c01v1BufferUnderf1Trap NOTIFICATION-TYPE
		OBJECTS { trapCounter, aip2000c01v1Index, aip2000c01v1BufferUnderf1 }
		STATUS current
		DESCRIPTION
			"Buffer underflow Trap"
		::= { aip2000c01v1Traps 113 }

		-- 1.3.6.1.4.1.10106.2.1.1.592901.3
		aip2000c01v1BufferOverf1Trap NOTIFICATION-TYPE
		OBJECTS { trapCounter, aip2000c01v1Index, aip2000c01v1BufferOverf1 }
		STATUS current
		DESCRIPTION
			"Buffer_overflow/TS error Trap"
		::= { aip2000c01v1Traps 115 }

		-- 1.3.6.1.4.1.10106.2.1.1.592901.3
		aip2000c01v1MalformedPck1Trap NOTIFICATION-TYPE
		OBJECTS { trapCounter, aip2000c01v1Index, aip2000c01v1MalformedPck1 }
		STATUS current
		DESCRIPTION
			"Malformed packets Trap"
		::= { aip2000c01v1Traps 117 }

		-- 1.3.6.1.4.1.10106.2.1.1.592901.3
		aip2000c01v1StreamOk2Trap NOTIFICATION-TYPE
		OBJECTS { trapCounter, aip2000c01v1Index, aip2000c01v1StreamOk2 }
		STATUS current
		DESCRIPTION
			"AES67 RX2 stream received Trap"
		::= { aip2000c01v1Traps 129 }

		-- 1.3.6.1.4.1.10106.2.1.1.592901.3
		aip2000c01v1BufferUnderf2Trap NOTIFICATION-TYPE
		OBJECTS { trapCounter, aip2000c01v1Index, aip2000c01v1BufferUnderf2 }
		STATUS current
		DESCRIPTION
			"Buffer underflow Trap"
		::= { aip2000c01v1Traps 131 }

		-- 1.3.6.1.4.1.10106.2.1.1.592901.3
		aip2000c01v1BufferOverf2Trap NOTIFICATION-TYPE
		OBJECTS { trapCounter, aip2000c01v1Index, aip2000c01v1BufferOverf2 }
		STATUS current
		DESCRIPTION
			"Buffer_overflow/TS error Trap"
		::= { aip2000c01v1Traps 133 }

		-- 1.3.6.1.4.1.10106.2.1.1.592901.3
		aip2000c01v1MalformedPck2Trap NOTIFICATION-TYPE
		OBJECTS { trapCounter, aip2000c01v1Index, aip2000c01v1MalformedPck2 }
		STATUS current
		DESCRIPTION
			"Malformed packets Trap"
		::= { aip2000c01v1Traps 135 }

		-- 1.3.6.1.4.1.10106.2.1.1.592901.3
		aip2000c01v1StreamOk3Trap NOTIFICATION-TYPE
		OBJECTS { trapCounter, aip2000c01v1Index, aip2000c01v1StreamOk3 }
		STATUS current
		DESCRIPTION
			"AES67 RX3 stream received Trap"
		::= { aip2000c01v1Traps 147 }

		-- 1.3.6.1.4.1.10106.2.1.1.592901.3
		aip2000c01v1BufferUnderf3Trap NOTIFICATION-TYPE
		OBJECTS { trapCounter, aip2000c01v1Index, aip2000c01v1BufferUnderf3 }
		STATUS current
		DESCRIPTION
			"Buffer underflow Trap"
		::= { aip2000c01v1Traps 149 }

		-- 1.3.6.1.4.1.10106.2.1.1.592901.3
		aip2000c01v1BufferOverf3Trap NOTIFICATION-TYPE
		OBJECTS { trapCounter, aip2000c01v1Index, aip2000c01v1BufferOverf3 }
		STATUS current
		DESCRIPTION
			"Buffer_overflow/TS error Trap"
		::= { aip2000c01v1Traps 151 }

		-- 1.3.6.1.4.1.10106.2.1.1.592901.3
		aip2000c01v1MalformedPck3Trap NOTIFICATION-TYPE
		OBJECTS { trapCounter, aip2000c01v1Index, aip2000c01v1MalformedPck3 }
		STATUS current
		DESCRIPTION
			"Malformed packets Trap"
		::= { aip2000c01v1Traps 153 }

		-- 1.3.6.1.4.1.10106.2.1.1.592901.3
		aip2000c01v1StreamOk4Trap NOTIFICATION-TYPE
		OBJECTS { trapCounter, aip2000c01v1Index, aip2000c01v1StreamOk4 }
		STATUS current
		DESCRIPTION
			"AES67 RX4 stream received Trap"
		::= { aip2000c01v1Traps 165 }

		-- 1.3.6.1.4.1.10106.2.1.1.592901.3
		aip2000c01v1BufferUnderf4Trap NOTIFICATION-TYPE
		OBJECTS { trapCounter, aip2000c01v1Index, aip2000c01v1BufferUnderf4 }
		STATUS current
		DESCRIPTION
			"Buffer underflow Trap"
		::= { aip2000c01v1Traps 167 }

		-- 1.3.6.1.4.1.10106.2.1.1.592901.3
		aip2000c01v1BufferOverf4Trap NOTIFICATION-TYPE
		OBJECTS { trapCounter, aip2000c01v1Index, aip2000c01v1BufferOverf4 }
		STATUS current
		DESCRIPTION
			"Buffer_overflow/TS error Trap"
		::= { aip2000c01v1Traps 169 }

		-- 1.3.6.1.4.1.10106.2.1.1.592901.3
		aip2000c01v1MalformedPck4Trap NOTIFICATION-TYPE
		OBJECTS { trapCounter, aip2000c01v1Index, aip2000c01v1MalformedPck4 }
		STATUS current
		DESCRIPTION
			"Malformed packets Trap"
		::= { aip2000c01v1Traps 171 }

		-- 1.3.6.1.4.1.10106.2.1.1.592901.3
		aip2000c01v1ShufOkTrap NOTIFICATION-TYPE
		OBJECTS { trapCounter, aip2000c01v1Index, aip2000c01v1ShufOk }
		STATUS current
		DESCRIPTION
			"Shuffling ok Trap"
		::= { aip2000c01v1Traps 191 }

		-- 1.3.6.1.4.1.10106.2.1.1.592901.3
		aip2000c01v1Link1Trap NOTIFICATION-TYPE
		OBJECTS { trapCounter, aip2000c01v1Index, aip2000c01v1Link1 }
		STATUS current
		DESCRIPTION
			"Ethernet conection status Trap"
		::= { aip2000c01v1Traps 195 }

		-- 1.3.6.1.4.1.10106.2.1.1.592901.3
		aip2000c01v1System1Trap NOTIFICATION-TYPE
		OBJECTS { trapCounter, aip2000c01v1Index, aip2000c01v1System1 }
		STATUS current
		DESCRIPTION
			"Ethernet conection system Trap"
		::= { aip2000c01v1Traps 197 }

		-- 1.3.6.1.4.1.10106.2.1.1.592901.3
		aip2000c01v1Link2Trap NOTIFICATION-TYPE
		OBJECTS { trapCounter, aip2000c01v1Index, aip2000c01v1Link2 }
		STATUS current
		DESCRIPTION
			"Ethernet conection status Trap"
		::= { aip2000c01v1Traps 199 }

		-- 1.3.6.1.4.1.10106.2.1.1.592901.3
		aip2000c01v1System2Trap NOTIFICATION-TYPE
		OBJECTS { trapCounter, aip2000c01v1Index, aip2000c01v1System2 }
		STATUS current
		DESCRIPTION
			"Ethernet conection system Trap"
		::= { aip2000c01v1Traps 201 }

		-- 1.3.6.1.4.1.10106.2.1.1.592901.3
		aip2000c01v1NoSignalTrap NOTIFICATION-TYPE
		OBJECTS { trapCounter, aip2000c01v1Index, aip2000c01v1NoSignal }
		STATUS current
		DESCRIPTION
			"There is no SDI signal or the format is not supported Trap"
		::= { aip2000c01v1Traps 203 }

		-- 1.3.6.1.4.1.10106.2.1.1.592901.3
		aip2000c01v1UnlockTrap NOTIFICATION-TYPE
		OBJECTS { trapCounter, aip2000c01v1Index, aip2000c01v1Unlock }
		STATUS current
		DESCRIPTION
			"Indicates signal unlock fail Trap"
		::= { aip2000c01v1Traps 205 }

		-- 1.3.6.1.4.1.10106.2.1.1.592901.3
		aip2000c01v1FormatTrap NOTIFICATION-TYPE
		OBJECTS { trapCounter, aip2000c01v1Index, aip2000c01v1Format }
		STATUS current
		DESCRIPTION
			"Indicates the SDI received signal format Trap"
		::= { aip2000c01v1Traps 209 }

		-- 1.3.6.1.4.1.10106.2.1.1.592901.3
		aip2000c01v1PtpStateTrap NOTIFICATION-TYPE
		OBJECTS { trapCounter, aip2000c01v1Index, aip2000c01v1PtpState }
		STATUS current
		DESCRIPTION
			"Indicates the PTP state Trap"
		::= { aip2000c01v1Traps 211 }

		-- 1.3.6.1.4.1.10106.2.1.1.592901.3
		aip2000c01v1TxWorkinStat1Trap NOTIFICATION-TYPE
		OBJECTS { trapCounter, aip2000c01v1Index, aip2000c01v1TxWorkinStat1 }
		STATUS current
		DESCRIPTION
			"TX1 transmitting Trap"
		::= { aip2000c01v1Traps 213 }

		-- 1.3.6.1.4.1.10106.2.1.1.592901.3
		aip2000c01v1ArpValid1Trap NOTIFICATION-TYPE
		OBJECTS { trapCounter, aip2000c01v1Index, aip2000c01v1ArpValid1 }
		STATUS current
		DESCRIPTION
			"TX1 valid ARP response (Unicast mode) Trap"
		::= { aip2000c01v1Traps 215 }

		-- 1.3.6.1.4.1.10106.2.1.1.592901.3
		aip2000c01v1IcmpError1Trap NOTIFICATION-TYPE
		OBJECTS { trapCounter, aip2000c01v1Index, aip2000c01v1IcmpError1 }
		STATUS current
		DESCRIPTION
			"TX1 destination unreachable (ICMP destination unrechable packets received) Trap"
		::= { aip2000c01v1Traps 217 }

		-- 1.3.6.1.4.1.10106.2.1.1.592901.3
		aip2000c01v1TxWorkinStat2Trap NOTIFICATION-TYPE
		OBJECTS { trapCounter, aip2000c01v1Index, aip2000c01v1TxWorkinStat2 }
		STATUS current
		DESCRIPTION
			"TX2 transmitting Trap"
		::= { aip2000c01v1Traps 219 }

		-- 1.3.6.1.4.1.10106.2.1.1.592901.3
		aip2000c01v1ArpValid2Trap NOTIFICATION-TYPE
		OBJECTS { trapCounter, aip2000c01v1Index, aip2000c01v1ArpValid2 }
		STATUS current
		DESCRIPTION
			"TX2 valid ARP response (Unicast mode) Trap"
		::= { aip2000c01v1Traps 221 }

		-- 1.3.6.1.4.1.10106.2.1.1.592901.3
		aip2000c01v1IcmpError2Trap NOTIFICATION-TYPE
		OBJECTS { trapCounter, aip2000c01v1Index, aip2000c01v1IcmpError2 }
		STATUS current
		DESCRIPTION
			"TX2 destination unreachable (ICMP destination unrechable packets received) Trap"
		::= { aip2000c01v1Traps 223 }

		-- 1.3.6.1.4.1.10106.2.1.1.592901.3
		aip2000c01v1TxWorkinStat3Trap NOTIFICATION-TYPE
		OBJECTS { trapCounter, aip2000c01v1Index, aip2000c01v1TxWorkinStat3 }
		STATUS current
		DESCRIPTION
			"TX3 transmitting Trap"
		::= { aip2000c01v1Traps 225 }

		-- 1.3.6.1.4.1.10106.2.1.1.592901.3
		aip2000c01v1ArpValid3Trap NOTIFICATION-TYPE
		OBJECTS { trapCounter, aip2000c01v1Index, aip2000c01v1ArpValid3 }
		STATUS current
		DESCRIPTION
			"TX3 valid ARP response (Unicast mode) Trap"
		::= { aip2000c01v1Traps 227 }

		-- 1.3.6.1.4.1.10106.2.1.1.592901.3
		aip2000c01v1IcmpError3Trap NOTIFICATION-TYPE
		OBJECTS { trapCounter, aip2000c01v1Index, aip2000c01v1IcmpError3 }
		STATUS current
		DESCRIPTION
			"TX3 destination unreachable (ICMP destination unrechable packets received) Trap"
		::= { aip2000c01v1Traps 229 }

		-- 1.3.6.1.4.1.10106.2.1.1.592901.3
		aip2000c01v1TxWorkinStat4Trap NOTIFICATION-TYPE
		OBJECTS { trapCounter, aip2000c01v1Index, aip2000c01v1TxWorkinStat4 }
		STATUS current
		DESCRIPTION
			"TX4 transmitting Trap"
		::= { aip2000c01v1Traps 231 }

		-- 1.3.6.1.4.1.10106.2.1.1.592901.3
		aip2000c01v1ArpValid4Trap NOTIFICATION-TYPE
		OBJECTS { trapCounter, aip2000c01v1Index, aip2000c01v1ArpValid4 }
		STATUS current
		DESCRIPTION
			"TX4 valid ARP response (Unicast mode) Trap"
		::= { aip2000c01v1Traps 233 }

		-- 1.3.6.1.4.1.10106.2.1.1.592901.3
		aip2000c01v1IcmpError4Trap NOTIFICATION-TYPE
		OBJECTS { trapCounter, aip2000c01v1Index, aip2000c01v1IcmpError4 }
		STATUS current
		DESCRIPTION
			"TX4 destination unreachable (ICMP destination unrechable packets received) Trap"
		::= { aip2000c01v1Traps 235 }

		-- 1.3.6.1.4.1.10106.2.1.1.592901.3
		aip2000c01v1AsrcUnlocked1Trap NOTIFICATION-TYPE
		OBJECTS { trapCounter, aip2000c01v1Index, aip2000c01v1AsrcUnlocked1 }
		STATUS current
		DESCRIPTION
			"ASRC unlocked (AES67->SDI) Trap"
		::= { aip2000c01v1Traps 237 }

		-- 1.3.6.1.4.1.10106.2.1.1.592901.3
		aip2000c01v1ProcessorStat1Trap NOTIFICATION-TYPE
		OBJECTS { trapCounter, aip2000c01v1Index, aip2000c01v1ProcessorStat1 }
		STATUS current
		DESCRIPTION
			"Processor syinchronization fail (AES67->SDI) Trap"
		::= { aip2000c01v1Traps 239 }

		-- 1.3.6.1.4.1.10106.2.1.1.592901.3
		aip2000c01v1AsrcUnlocked2Trap NOTIFICATION-TYPE
		OBJECTS { trapCounter, aip2000c01v1Index, aip2000c01v1AsrcUnlocked2 }
		STATUS current
		DESCRIPTION
			"ASRC unlocked (SDI->AES67) Trap"
		::= { aip2000c01v1Traps 241 }

		-- 1.3.6.1.4.1.10106.2.1.1.592901.3
		aip2000c01v1ProcessorStat2Trap NOTIFICATION-TYPE
		OBJECTS { trapCounter, aip2000c01v1Index, aip2000c01v1ProcessorStat2 }
		STATUS current
		DESCRIPTION
			"Processor syinchronization fail (SDI->AES67) Trap"
		::= { aip2000c01v1Traps 243 }

		-- 1.3.6.1.4.1.10106.2.1.1.592901.3
		aip2000c01v1Seamless0Trap NOTIFICATION-TYPE
		OBJECTS { trapCounter, aip2000c01v1Index, aip2000c01v1Seamless0 }
		STATUS current
		DESCRIPTION
			"Seamless capable RX1/RX2 Trap"
		::= { aip2000c01v1Traps 245 }

		-- 1.3.6.1.4.1.10106.2.1.1.592901.3
		aip2000c01v1Seamless1Trap NOTIFICATION-TYPE
		OBJECTS { trapCounter, aip2000c01v1Index, aip2000c01v1Seamless1 }
		STATUS current
		DESCRIPTION
			"Seamless capable RX3/RX4 Trap"
		::= { aip2000c01v1Traps 247 }

		-- 1.3.6.1.4.1.10106.2.1.1.592901.3
		aip2000c01v1ClkStatusTrap NOTIFICATION-TYPE
		OBJECTS { trapCounter, aip2000c01v1Index, aip2000c01v1ClkStatus }
		STATUS current
		DESCRIPTION
			"Clock status Trap"
		::= { aip2000c01v1Traps 249 }

		-- 1.3.6.1.4.1.10106.2.1.1.592901.3
		aip2000c01v1Grp1PresTrap NOTIFICATION-TYPE
		OBJECTS { trapCounter, aip2000c01v1Index, aip2000c01v1Grp1Pres }
		STATUS current
		DESCRIPTION
			"Group 1 presence Trap"
		::= { aip2000c01v1Traps 251 }

		-- 1.3.6.1.4.1.10106.2.1.1.592901.3
		aip2000c01v1PresenciaMpxTrap NOTIFICATION-TYPE
		OBJECTS { trapCounter, aip2000c01v1Index, aip2000c01v1PresenciaMpx }
		STATUS current
		DESCRIPTION
			"MPX presence: channels 1-8 Trap"
		::= { aip2000c01v1Traps 253 }

		-- 1.3.6.1.4.1.10106.2.1.1.592901.3
		aip2000c01v1Grp2PresTrap NOTIFICATION-TYPE
		OBJECTS { trapCounter, aip2000c01v1Index, aip2000c01v1Grp2Pres }
		STATUS current
		DESCRIPTION
			"Group 2 presence Trap"
		::= { aip2000c01v1Traps 255 }

		-- 1.3.6.1.4.1.10106.2.1.1.592901.3
		aip2000c01v1Grp3PresTrap NOTIFICATION-TYPE
		OBJECTS { trapCounter, aip2000c01v1Index, aip2000c01v1Grp3Pres }
		STATUS current
		DESCRIPTION
			"Group 3 presence Trap"
		::= { aip2000c01v1Traps 257 }

		-- 1.3.6.1.4.1.10106.2.1.1.592901.3
		aip2000c01v1Grp4PresTrap NOTIFICATION-TYPE
		OBJECTS { trapCounter, aip2000c01v1Index, aip2000c01v1Grp4Pres }
		STATUS current
		DESCRIPTION
			"Group 4 presence Trap"
		::= { aip2000c01v1Traps 259 }

		-- 1.3.6.1.4.1.10106.2.1.1.593001
		asd2008c01v1Traps OBJECT IDENTIFIER ::= { albalaTraps 593001 }

		-- 1.3.6.1.4.1.10106.2.1.1.593001.3
		asd2008c01v1SampFreqTrap NOTIFICATION-TYPE
		OBJECTS { trapCounter, asd2008c01v1Index, asd2008c01v1SampFreq }
		STATUS current
		DESCRIPTION
			"Sampling frequency used in the received transport stream Trap"
		::= { asd2008c01v1Traps 7 }

		-- 1.3.6.1.4.1.10106.2.1.1.593001.3
		asd2008c01v1BitsPerSampTrap NOTIFICATION-TYPE
		OBJECTS { trapCounter, asd2008c01v1Index, asd2008c01v1BitsPerSamp }
		STATUS current
		DESCRIPTION
			"Bits per audio sample used in the received transport stream Trap"
		::= { asd2008c01v1Traps 9 }

		-- 1.3.6.1.4.1.10106.2.1.1.593001.3
		asd2008c01v1AudClipTrap NOTIFICATION-TYPE
		OBJECTS { trapCounter, asd2008c01v1Index, asd2008c01v1AudClip }
		STATUS current
		DESCRIPTION
			"Indicates clipping due to excessive applied gain Trap"
		::= { asd2008c01v1Traps 11 }

		-- 1.3.6.1.4.1.10106.2.1.1.593001.3
		asd2008c01v1TsLockTrap NOTIFICATION-TYPE
		OBJECTS { trapCounter, asd2008c01v1Index, asd2008c01v1TsLock }
		STATUS current
		DESCRIPTION
			"Transport Stream not present at input or invalid Trap"
		::= { asd2008c01v1Traps 13 }

		-- 1.3.6.1.4.1.10106.2.1.1.593001.3
		asd2008c01v1PhaseLockTrap NOTIFICATION-TYPE
		OBJECTS { trapCounter, asd2008c01v1Index, asd2008c01v1PhaseLock }
		STATUS current
		DESCRIPTION
			"Output not locked to transport stream source Trap"
		::= { asd2008c01v1Traps 15 }

		-- 1.3.6.1.4.1.10106.2.1.1.593001.3
		asd2008c01v1ChPres1Trap NOTIFICATION-TYPE
		OBJECTS { trapCounter, asd2008c01v1Index, asd2008c01v1ChPres1 }
		STATUS current
		DESCRIPTION
			"Channel present in received Transport Stream Trap"
		::= { asd2008c01v1Traps 17 }

		-- 1.3.6.1.4.1.10106.2.1.1.593001.3
		asd2008c01v1ChPres2Trap NOTIFICATION-TYPE
		OBJECTS { trapCounter, asd2008c01v1Index, asd2008c01v1ChPres2 }
		STATUS current
		DESCRIPTION
			"Channel present in received Transport Stream Trap"
		::= { asd2008c01v1Traps 19 }

		-- 1.3.6.1.4.1.10106.2.1.1.593001.3
		asd2008c01v1ChPres3Trap NOTIFICATION-TYPE
		OBJECTS { trapCounter, asd2008c01v1Index, asd2008c01v1ChPres3 }
		STATUS current
		DESCRIPTION
			"Channel present in received Transport Stream Trap"
		::= { asd2008c01v1Traps 21 }

		-- 1.3.6.1.4.1.10106.2.1.1.593001.3
		asd2008c01v1ChPres4Trap NOTIFICATION-TYPE
		OBJECTS { trapCounter, asd2008c01v1Index, asd2008c01v1ChPres4 }
		STATUS current
		DESCRIPTION
			"Channel present in received Transport Stream Trap"
		::= { asd2008c01v1Traps 23 }

		-- 1.3.6.1.4.1.10106.2.1.1.593001.3
		asd2008c01v1ChPres5Trap NOTIFICATION-TYPE
		OBJECTS { trapCounter, asd2008c01v1Index, asd2008c01v1ChPres5 }
		STATUS current
		DESCRIPTION
			"Channel present in received Transport Stream Trap"
		::= { asd2008c01v1Traps 25 }

		-- 1.3.6.1.4.1.10106.2.1.1.593001.3
		asd2008c01v1ChPres6Trap NOTIFICATION-TYPE
		OBJECTS { trapCounter, asd2008c01v1Index, asd2008c01v1ChPres6 }
		STATUS current
		DESCRIPTION
			"Channel present in received Transport Stream Trap"
		::= { asd2008c01v1Traps 27 }

		-- 1.3.6.1.4.1.10106.2.1.1.593001.3
		asd2008c01v1ChPres7Trap NOTIFICATION-TYPE
		OBJECTS { trapCounter, asd2008c01v1Index, asd2008c01v1ChPres7 }
		STATUS current
		DESCRIPTION
			"Channel present in received Transport Stream Trap"
		::= { asd2008c01v1Traps 29 }

		-- 1.3.6.1.4.1.10106.2.1.1.593001.3
		asd2008c01v1ChPres8Trap NOTIFICATION-TYPE
		OBJECTS { trapCounter, asd2008c01v1Index, asd2008c01v1ChPres8 }
		STATUS current
		DESCRIPTION
			"Channel present in received Transport Stream Trap"
		::= { asd2008c01v1Traps 31 }

		-- 1.3.6.1.4.1.10106.2.1.1.599301
		ded2008c01v1Traps OBJECT IDENTIFIER ::= { albalaTraps 599301 }

		-- 1.3.6.1.4.1.10106.2.1.1.599301.3
		ded2008c01v1SdiInFailTrap NOTIFICATION-TYPE
		OBJECTS { trapCounter, ded2008c01v1Index, ded2008c01v1SdiInFail }
		STATUS current
		DESCRIPTION
			"No signal present in SDI input Trap"
		::= { ded2008c01v1Traps 67 }

		-- 1.3.6.1.4.1.10106.2.1.1.599301.3
		ded2008c01v1SdiG1FailTrap NOTIFICATION-TYPE
		OBJECTS { trapCounter, ded2008c01v1Index, ded2008c01v1SdiG1Fail }
		STATUS current
		DESCRIPTION
			"Audio group 1 not present in input SDI signal Trap"
		::= { ded2008c01v1Traps 69 }

		-- 1.3.6.1.4.1.10106.2.1.1.599301.3
		ded2008c01v1SdiG2FailTrap NOTIFICATION-TYPE
		OBJECTS { trapCounter, ded2008c01v1Index, ded2008c01v1SdiG2Fail }
		STATUS current
		DESCRIPTION
			"Audio group 2 not present in input SDI signal Trap"
		::= { ded2008c01v1Traps 71 }

		-- 1.3.6.1.4.1.10106.2.1.1.599301.3
		ded2008c01v1SdiG3FailTrap NOTIFICATION-TYPE
		OBJECTS { trapCounter, ded2008c01v1Index, ded2008c01v1SdiG3Fail }
		STATUS current
		DESCRIPTION
			"Audio group 3 not present in input SDI signal Trap"
		::= { ded2008c01v1Traps 73 }

		-- 1.3.6.1.4.1.10106.2.1.1.599301.3
		ded2008c01v1SdiG4FailTrap NOTIFICATION-TYPE
		OBJECTS { trapCounter, ded2008c01v1Index, ded2008c01v1SdiG4Fail }
		STATUS current
		DESCRIPTION
			"Audio group 4 not present in input SDI signal Trap"
		::= { ded2008c01v1Traps 75 }

		-- 1.3.6.1.4.1.10106.2.1.1.599301.3
		ded2008c01v1Ref27mFailTrap NOTIFICATION-TYPE
		OBJECTS { trapCounter, ded2008c01v1Index, ded2008c01v1Ref27mFail }
		STATUS current
		DESCRIPTION
			"No 27 MHz reference coming from slot on the right Trap"
		::= { ded2008c01v1Traps 77 }

		-- 1.3.6.1.4.1.10106.2.1.1.599301.3
		ded2008c01v1AudioProcFailTrap NOTIFICATION-TYPE
		OBJECTS { trapCounter, ded2008c01v1Index, ded2008c01v1AudioProcFail }
		STATUS current
		DESCRIPTION
			"Indicates an invalid configuration or input error Trap"
		::= { ded2008c01v1Traps 79 }

		-- 1.3.6.1.4.1.10106.2.1.1.599301.3
		ded2008c01v1In1AudFailTrap NOTIFICATION-TYPE
		OBJECTS { trapCounter, ded2008c01v1Index, ded2008c01v1In1AudFail }
		STATUS current
		DESCRIPTION
			"No signal in IN1 input Trap"
		::= { ded2008c01v1Traps 81 }

		-- 1.3.6.1.4.1.10106.2.1.1.599301.3
		ded2008c01v1In1RefFailTrap NOTIFICATION-TYPE
		OBJECTS { trapCounter, ded2008c01v1Index, ded2008c01v1In1RefFail }
		STATUS current
		DESCRIPTION
			"No reference present in IN1 Trap"
		::= { ded2008c01v1Traps 83 }

		-- 1.3.6.1.4.1.10106.2.1.1.599301.3
		ded2008c01v1In2AudFailTrap NOTIFICATION-TYPE
		OBJECTS { trapCounter, ded2008c01v1Index, ded2008c01v1In2AudFail }
		STATUS current
		DESCRIPTION
			"No signal in IN2 input Trap"
		::= { ded2008c01v1Traps 85 }

		-- 1.3.6.1.4.1.10106.2.1.1.599301.3
		ded2008c01v1In2RefFailTrap NOTIFICATION-TYPE
		OBJECTS { trapCounter, ded2008c01v1Index, ded2008c01v1In2RefFail }
		STATUS current
		DESCRIPTION
			"No reference present in IN2 Trap"
		::= { ded2008c01v1Traps 87 }

		-- 1.3.6.1.4.1.10106.2.1.1.599301.3
		ded2008c01v1In3AudFailTrap NOTIFICATION-TYPE
		OBJECTS { trapCounter, ded2008c01v1Index, ded2008c01v1In3AudFail }
		STATUS current
		DESCRIPTION
			"No signal in IN3 input Trap"
		::= { ded2008c01v1Traps 89 }

		-- 1.3.6.1.4.1.10106.2.1.1.599301.3
		ded2008c01v1In3RefFailTrap NOTIFICATION-TYPE
		OBJECTS { trapCounter, ded2008c01v1Index, ded2008c01v1In3RefFail }
		STATUS current
		DESCRIPTION
			"No reference present in IN3 Trap"
		::= { ded2008c01v1Traps 91 }

		-- 1.3.6.1.4.1.10106.2.1.1.599301.3
		ded2008c01v1In4AudFailTrap NOTIFICATION-TYPE
		OBJECTS { trapCounter, ded2008c01v1Index, ded2008c01v1In4AudFail }
		STATUS current
		DESCRIPTION
			"No signal in IN4 input Trap"
		::= { ded2008c01v1Traps 93 }

		-- 1.3.6.1.4.1.10106.2.1.1.599301.3
		ded2008c01v1In4RefFailTrap NOTIFICATION-TYPE
		OBJECTS { trapCounter, ded2008c01v1Index, ded2008c01v1In4RefFail }
		STATUS current
		DESCRIPTION
			"No reference present in IN4 Trap"
		::= { ded2008c01v1Traps 95 }

		-- 1.3.6.1.4.1.10106.2.1.1.599301.3
		ded2008c01v1In5AudFailTrap NOTIFICATION-TYPE
		OBJECTS { trapCounter, ded2008c01v1Index, ded2008c01v1In5AudFail }
		STATUS current
		DESCRIPTION
			"No signal in IN5 input Trap"
		::= { ded2008c01v1Traps 97 }

		-- 1.3.6.1.4.1.10106.2.1.1.599301.3
		ded2008c01v1In6AudFailTrap NOTIFICATION-TYPE
		OBJECTS { trapCounter, ded2008c01v1Index, ded2008c01v1In6AudFail }
		STATUS current
		DESCRIPTION
			"No signal in IN6 input Trap"
		::= { ded2008c01v1Traps 99 }

		-- 1.3.6.1.4.1.10106.2.1.1.599301.3
		ded2008c01v1In7AudFailTrap NOTIFICATION-TYPE
		OBJECTS { trapCounter, ded2008c01v1Index, ded2008c01v1In7AudFail }
		STATUS current
		DESCRIPTION
			"No signal in IN7 input Trap"
		::= { ded2008c01v1Traps 101 }

		-- 1.3.6.1.4.1.10106.2.1.1.599301.3
		ded2008c01v1In8AudFailTrap NOTIFICATION-TYPE
		OBJECTS { trapCounter, ded2008c01v1Index, ded2008c01v1In8AudFail }
		STATUS current
		DESCRIPTION
			"No signal in IN8 input Trap"
		::= { ded2008c01v1Traps 103 }

		-- 1.3.6.1.4.1.10106.2.1.1.600801
		uvd2000c01v1Traps OBJECT IDENTIFIER ::= { albalaTraps 600801 }

		-- 1.3.6.1.4.1.10106.2.1.1.600801.3
		uvd2000c01v1InputTrap NOTIFICATION-TYPE
		OBJECTS { trapCounter, uvd2000c01v1Index, uvd2000c01v1Input }
		STATUS current
		DESCRIPTION
			"Indicates the input selected Trap"
		::= { uvd2000c01v1Traps 3 }

		-- 1.3.6.1.4.1.10106.2.1.1.600801.3
		uvd2000c01v1LosTrap NOTIFICATION-TYPE
		OBJECTS { trapCounter, uvd2000c01v1Index, uvd2000c01v1Los }
		STATUS current
		DESCRIPTION
			"Indicates a loss of signal Trap"
		::= { uvd2000c01v1Traps 7 }

		-- 1.3.6.1.4.1.10106.2.1.1.600801.3
		uvd2000c01v1UnlockTrap NOTIFICATION-TYPE
		OBJECTS { trapCounter, uvd2000c01v1Index, uvd2000c01v1Unlock }
		STATUS current
		DESCRIPTION
			"Indicates signal unlock fail Trap"
		::= { uvd2000c01v1Traps 9 }

		-- 1.3.6.1.4.1.10106.2.1.1.600801.3
		uvd2000c01v1RateTrap NOTIFICATION-TYPE
		OBJECTS { trapCounter, uvd2000c01v1Index, uvd2000c01v1Rate }
		STATUS current
		DESCRIPTION
			"Indicates the SDI signal type Trap"
		::= { uvd2000c01v1Traps 11 }

		-- 1.3.6.1.4.1.10106.2.1.1.607801
		deb2008c01v1Traps OBJECT IDENTIFIER ::= { albalaTraps 607801 }

		-- 1.3.6.1.4.1.10106.2.1.1.607801.3
		deb2008c01v1AudClipErTrap NOTIFICATION-TYPE
		OBJECTS { trapCounter, deb2008c01v1Index, deb2008c01v1AudClipEr }
		STATUS current
		DESCRIPTION
			"Audio clipping error Trap"
		::= { deb2008c01v1Traps 119 }

		-- 1.3.6.1.4.1.10106.2.1.1.607801.3
		deb2008c01v1AudPresFailTrap NOTIFICATION-TYPE
		OBJECTS { trapCounter, deb2008c01v1Index, deb2008c01v1AudPresFail }
		STATUS current
		DESCRIPTION
			"It lights up when the backplane bus does not have all the audio channels the module is required to read Trap"
		::= { deb2008c01v1Traps 121 }

		-- 1.3.6.1.4.1.10106.2.1.1.607801.3
		deb2008c01v1AudInsFailTrap NOTIFICATION-TYPE
		OBJECTS { trapCounter, deb2008c01v1Index, deb2008c01v1AudInsFail }
		STATUS current
		DESCRIPTION
			"It lights up when the module cannot insert in the backplane bus the audio channels Trap"
		::= { deb2008c01v1Traps 123 }

		-- 1.3.6.1.4.1.10106.2.1.1.607801.3
		deb2008c01v1AudOvldErTrap NOTIFICATION-TYPE
		OBJECTS { trapCounter, deb2008c01v1Index, deb2008c01v1AudOvldEr }
		STATUS current
		DESCRIPTION
			"Audio overload fail Trap"
		::= { deb2008c01v1Traps 125 }

		-- 1.3.6.1.4.1.10106.2.1.1.607901
		def2008c01v1Traps OBJECT IDENTIFIER ::= { albalaTraps 607901 }

		-- 1.3.6.1.4.1.10106.2.1.1.607901.3
		def2008c01v1AesIn1PresTrap NOTIFICATION-TYPE
		OBJECTS { trapCounter, def2008c01v1Index, def2008c01v1AesIn1Pres }
		STATUS current
		DESCRIPTION
			"AES1 IN presence (valid signal) Trap"
		::= { def2008c01v1Traps 37 }

		-- 1.3.6.1.4.1.10106.2.1.1.607901.3
		def2008c01v1Aes1RefPresTrap NOTIFICATION-TYPE
		OBJECTS { trapCounter, def2008c01v1Index, def2008c01v1Aes1RefPres }
		STATUS current
		DESCRIPTION
			"AES1 reference presence Trap"
		::= { def2008c01v1Traps 39 }

		-- 1.3.6.1.4.1.10106.2.1.1.607901.3
		def2008c01v1AesIn2PresTrap NOTIFICATION-TYPE
		OBJECTS { trapCounter, def2008c01v1Index, def2008c01v1AesIn2Pres }
		STATUS current
		DESCRIPTION
			"AES2 IN presence (valid signal) Trap"
		::= { def2008c01v1Traps 41 }

		-- 1.3.6.1.4.1.10106.2.1.1.607901.3
		def2008c01v1Aes2RefPresTrap NOTIFICATION-TYPE
		OBJECTS { trapCounter, def2008c01v1Index, def2008c01v1Aes2RefPres }
		STATUS current
		DESCRIPTION
			"AES2 reference presence Trap"
		::= { def2008c01v1Traps 43 }

		-- 1.3.6.1.4.1.10106.2.1.1.607901.3
		def2008c01v1AesIn3PresTrap NOTIFICATION-TYPE
		OBJECTS { trapCounter, def2008c01v1Index, def2008c01v1AesIn3Pres }
		STATUS current
		DESCRIPTION
			"AES3 IN presence (valid signal) Trap"
		::= { def2008c01v1Traps 45 }

		-- 1.3.6.1.4.1.10106.2.1.1.607901.3
		def2008c01v1Aes3RefPresTrap NOTIFICATION-TYPE
		OBJECTS { trapCounter, def2008c01v1Index, def2008c01v1Aes3RefPres }
		STATUS current
		DESCRIPTION
			"AES3 reference presence Trap"
		::= { def2008c01v1Traps 47 }

		-- 1.3.6.1.4.1.10106.2.1.1.607901.3
		def2008c01v1AesIn4PresTrap NOTIFICATION-TYPE
		OBJECTS { trapCounter, def2008c01v1Index, def2008c01v1AesIn4Pres }
		STATUS current
		DESCRIPTION
			"AES4 IN presence (valid signal) Trap"
		::= { def2008c01v1Traps 49 }

		-- 1.3.6.1.4.1.10106.2.1.1.607901.3
		def2008c01v1Aes4RefPresTrap NOTIFICATION-TYPE
		OBJECTS { trapCounter, def2008c01v1Index, def2008c01v1Aes4RefPres }
		STATUS current
		DESCRIPTION
			"AES4 reference presence Trap"
		::= { def2008c01v1Traps 51 }

		-- 1.3.6.1.4.1.10106.2.1.1.607901.3
		def2008c01v1AesIn5PresTrap NOTIFICATION-TYPE
		OBJECTS { trapCounter, def2008c01v1Index, def2008c01v1AesIn5Pres }
		STATUS current
		DESCRIPTION
			"AES5 IN presence (valid signal) Trap"
		::= { def2008c01v1Traps 53 }

		-- 1.3.6.1.4.1.10106.2.1.1.607901.3
		def2008c01v1AesIn6PresTrap NOTIFICATION-TYPE
		OBJECTS { trapCounter, def2008c01v1Index, def2008c01v1AesIn6Pres }
		STATUS current
		DESCRIPTION
			"AES6 IN presence (valid signal) Trap"
		::= { def2008c01v1Traps 55 }

		-- 1.3.6.1.4.1.10106.2.1.1.607901.3
		def2008c01v1AesIn7PresTrap NOTIFICATION-TYPE
		OBJECTS { trapCounter, def2008c01v1Index, def2008c01v1AesIn7Pres }
		STATUS current
		DESCRIPTION
			"AES7 IN presence (valid signal) Trap"
		::= { def2008c01v1Traps 57 }

		-- 1.3.6.1.4.1.10106.2.1.1.607901.3
		def2008c01v1AesIn8PresTrap NOTIFICATION-TYPE
		OBJECTS { trapCounter, def2008c01v1Index, def2008c01v1AesIn8Pres }
		STATUS current
		DESCRIPTION
			"AES8 IN presence (valid signal) Trap"
		::= { def2008c01v1Traps 59 }

		-- 1.3.6.1.4.1.10106.2.1.1.607901.3
		def2008c01v1BackplaneLockedTrap NOTIFICATION-TYPE
		OBJECTS { trapCounter, def2008c01v1Index, def2008c01v1BackplaneLocked }
		STATUS current
		DESCRIPTION
			"Locked to internal bus audio (MCLK and WCLK valid and locked) Trap"
		::= { def2008c01v1Traps 77 }

		-- 1.3.6.1.4.1.10106.2.1.1.609201
		dad2000c01v1Traps OBJECT IDENTIFIER ::= { albalaTraps 609201 }

		-- 1.3.6.1.4.1.10106.2.1.1.609201.3
		dad2000c01v1SigFailTrap NOTIFICATION-TYPE
		OBJECTS { trapCounter, dad2000c01v1Index, dad2000c01v1SigFail }
		STATUS current
		DESCRIPTION
			"Indicates that a signal fail has been detected Trap"
		::= { dad2000c01v1Traps 3 }

		-- 1.3.6.1.4.1.10106.2.1.1.609201.3
		dad2000c01v1SigLowTrap NOTIFICATION-TYPE
		OBJECTS { trapCounter, dad2000c01v1Index, dad2000c01v1SigLow }
		STATUS current
		DESCRIPTION
			"Indicates that a signal low has been detected Trap"
		::= { dad2000c01v1Traps 5 }

		-- 1.3.6.1.4.1.10106.2.1.1.616301
		gpd2000c01v1Traps OBJECT IDENTIFIER ::= { albalaTraps 616301 }

		-- 1.3.6.1.4.1.10106.2.1.1.616301.3
		gpd2000c01v1VccGnss1FailTrap NOTIFICATION-TYPE
		OBJECTS { trapCounter, gpd2000c01v1Index, gpd2000c01v1VccGnss1Fail }
		STATUS current
		DESCRIPTION
			"VCC GNSS Input 1 fail Trap"
		::= { gpd2000c01v1Traps 9 }

		-- 1.3.6.1.4.1.10106.2.1.1.616301.3
		gpd2000c01v1VccGnss2FailTrap NOTIFICATION-TYPE
		OBJECTS { trapCounter, gpd2000c01v1Index, gpd2000c01v1VccGnss2Fail }
		STATUS current
		DESCRIPTION
			"VCC GNSS Input 2 fail Trap"
		::= { gpd2000c01v1Traps 11 }

		-- 1.3.6.1.4.1.10106.2.1.1.616301.3
		gpd2000c01v1VccGnss3FailTrap NOTIFICATION-TYPE
		OBJECTS { trapCounter, gpd2000c01v1Index, gpd2000c01v1VccGnss3Fail }
		STATUS current
		DESCRIPTION
			"VCC GNSS Input 3 fail Trap"
		::= { gpd2000c01v1Traps 13 }

		-- 1.3.6.1.4.1.10106.2.1.1.616301.3
		gpd2000c01v1VccGnss4FailTrap NOTIFICATION-TYPE
		OBJECTS { trapCounter, gpd2000c01v1Index, gpd2000c01v1VccGnss4Fail }
		STATUS current
		DESCRIPTION
			"VCC GNSS Input 4 fail Trap"
		::= { gpd2000c01v1Traps 15 }

		-- 1.3.6.1.4.1.10106.2.1.1.616301.3
		gpd2000c01v1VccAntennaFailTrap NOTIFICATION-TYPE
		OBJECTS { trapCounter, gpd2000c01v1Index, gpd2000c01v1VccAntennaFail }
		STATUS current
		DESCRIPTION
			"VCC antenna fail Trap"
		::= { gpd2000c01v1Traps 17 }

		-- 1.3.6.1.4.1.10106.2.1.1.616301.3
		gpd2000c01v1IccAntennaFailTrap NOTIFICATION-TYPE
		OBJECTS { trapCounter, gpd2000c01v1Index, gpd2000c01v1IccAntennaFail }
		STATUS current
		DESCRIPTION
			"ICC antenna fail Trap"
		::= { gpd2000c01v1Traps 19 }

		-- 1.3.6.1.4.1.10106.2.1.1.616301.3
		gpd2000c01v1NoAntennaTrap NOTIFICATION-TYPE
		OBJECTS { trapCounter, gpd2000c01v1Index, gpd2000c01v1NoAntenna }
		STATUS current
		DESCRIPTION
			"Antenna presence fail Trap"
		::= { gpd2000c01v1Traps 21 }

		-- 1.3.6.1.4.1.10106.2.1.1.620401
		hxc2000c02v1Traps OBJECT IDENTIFIER ::= { albalaTraps 620401 }

		-- 1.3.6.1.4.1.10106.2.1.1.620401.3
		hxc2000c02v1AnaRefFmtTrap NOTIFICATION-TYPE
		OBJECTS { trapCounter, hxc2000c02v1Index, hxc2000c02v1AnaRefFmt }
		STATUS current
		DESCRIPTION
			"Analog reference input format Trap"
		::= { hxc2000c02v1Traps 9 }

		-- 1.3.6.1.4.1.10106.2.1.1.620401.3
		hxc2000c02v1ModeConvTrap NOTIFICATION-TYPE
		OBJECTS { trapCounter, hxc2000c02v1Index, hxc2000c02v1ModeConv }
		STATUS current
		DESCRIPTION
			"Conversion mode Trap"
		::= { hxc2000c02v1Traps 17 }

		-- 1.3.6.1.4.1.10106.2.1.1.620401.3
		hxc2000c02v1OutAfdTrap NOTIFICATION-TYPE
		OBJECTS { trapCounter, hxc2000c02v1Index, hxc2000c02v1OutAfd }
		STATUS current
		DESCRIPTION
			"Output active format description Trap"
		::= { hxc2000c02v1Traps 19 }

		-- 1.3.6.1.4.1.10106.2.1.1.620401.3
		hxc2000c02v1OutCfTrap NOTIFICATION-TYPE
		OBJECTS { trapCounter, hxc2000c02v1Index, hxc2000c02v1OutCf }
		STATUS current
		DESCRIPTION
			"Output coded frame Trap"
		::= { hxc2000c02v1Traps 21 }

		-- 1.3.6.1.4.1.10106.2.1.1.620401.3
		hxc2000c02v1InAfdExpctTrap NOTIFICATION-TYPE
		OBJECTS { trapCounter, hxc2000c02v1Index, hxc2000c02v1InAfdExpct }
		STATUS current
		DESCRIPTION
			"Input expected active format description Trap"
		::= { hxc2000c02v1Traps 25 }

		-- 1.3.6.1.4.1.10106.2.1.1.620401.3
		hxc2000c02v1InCfExpctTrap NOTIFICATION-TYPE
		OBJECTS { trapCounter, hxc2000c02v1Index, hxc2000c02v1InCfExpct }
		STATUS current
		DESCRIPTION
			"Input expected coded frame Trap"
		::= { hxc2000c02v1Traps 27 }

		-- 1.3.6.1.4.1.10106.2.1.1.620401.3
		hxc2000c02v1TxFmtTrap NOTIFICATION-TYPE
		OBJECTS { trapCounter, hxc2000c02v1Index, hxc2000c02v1TxFmt }
		STATUS current
		DESCRIPTION
			"Output format Trap"
		::= { hxc2000c02v1Traps 29 }

		-- 1.3.6.1.4.1.10106.2.1.1.620401.3
		hxc2000c02v1DeintAlgorithmTrap NOTIFICATION-TYPE
		OBJECTS { trapCounter, hxc2000c02v1Index, hxc2000c02v1DeintAlgorithm }
		STATUS current
		DESCRIPTION
			"Allows selecting the de-interlacing algorithm Trap"
		::= { hxc2000c02v1Traps 31 }

		-- 1.3.6.1.4.1.10106.2.1.1.620401.3
		hxc2000c02v1InPhyFailTrap NOTIFICATION-TYPE
		OBJECTS { trapCounter, hxc2000c02v1Index, hxc2000c02v1InPhyFail }
		STATUS current
		DESCRIPTION
			"Absence fail Trap"
		::= { hxc2000c02v1Traps 87 }

		-- 1.3.6.1.4.1.10106.2.1.1.620401.3
		hxc2000c02v1InFmtFailTrap NOTIFICATION-TYPE
		OBJECTS { trapCounter, hxc2000c02v1Index, hxc2000c02v1InFmtFail }
		STATUS current
		DESCRIPTION
			"Format fail Trap"
		::= { hxc2000c02v1Traps 89 }

		-- 1.3.6.1.4.1.10106.2.1.1.620401.3
		hxc2000c02v1InIncFailTrap NOTIFICATION-TYPE
		OBJECTS { trapCounter, hxc2000c02v1Index, hxc2000c02v1InIncFail }
		STATUS current
		DESCRIPTION
			"Incompatible format fail Trap"
		::= { hxc2000c02v1Traps 91 }

		-- 1.3.6.1.4.1.10106.2.1.1.620401.3
		hxc2000c02v1InCrcFailTrap NOTIFICATION-TYPE
		OBJECTS { trapCounter, hxc2000c02v1Index, hxc2000c02v1InCrcFail }
		STATUS current
		DESCRIPTION
			"EDH/CRC fail Trap"
		::= { hxc2000c02v1Traps 95 }

		-- 1.3.6.1.4.1.10106.2.1.1.620401.3
		hxc2000c02v1PresAudG1FailTrap NOTIFICATION-TYPE
		OBJECTS { trapCounter, hxc2000c02v1Index, hxc2000c02v1PresAudG1Fail }
		STATUS current
		DESCRIPTION
			"Audio group 1 presence fail Trap"
		::= { hxc2000c02v1Traps 105 }

		-- 1.3.6.1.4.1.10106.2.1.1.620401.3
		hxc2000c02v1PresAudG2FailTrap NOTIFICATION-TYPE
		OBJECTS { trapCounter, hxc2000c02v1Index, hxc2000c02v1PresAudG2Fail }
		STATUS current
		DESCRIPTION
			"Audio group 2 presence fail Trap"
		::= { hxc2000c02v1Traps 107 }

		-- 1.3.6.1.4.1.10106.2.1.1.620401.3
		hxc2000c02v1PresAudG3FailTrap NOTIFICATION-TYPE
		OBJECTS { trapCounter, hxc2000c02v1Index, hxc2000c02v1PresAudG3Fail }
		STATUS current
		DESCRIPTION
			"Audio group 3 presence fail Trap"
		::= { hxc2000c02v1Traps 109 }

		-- 1.3.6.1.4.1.10106.2.1.1.620401.3
		hxc2000c02v1PresAudG4FailTrap NOTIFICATION-TYPE
		OBJECTS { trapCounter, hxc2000c02v1Index, hxc2000c02v1PresAudG4Fail }
		STATUS current
		DESCRIPTION
			"Audio group 4 presence fail Trap"
		::= { hxc2000c02v1Traps 111 }

		-- 1.3.6.1.4.1.10106.2.1.1.620401.3
		hxc2000c02v1RefFailTrap NOTIFICATION-TYPE
		OBJECTS { trapCounter, hxc2000c02v1Index, hxc2000c02v1RefFail }
		STATUS current
		DESCRIPTION
			"Analog reference absence fail Trap"
		::= { hxc2000c02v1Traps 113 }

		-- 1.3.6.1.4.1.10106.2.1.1.620401.3
		hxc2000c02v1RefFmtFailTrap NOTIFICATION-TYPE
		OBJECTS { trapCounter, hxc2000c02v1Index, hxc2000c02v1RefFmtFail }
		STATUS current
		DESCRIPTION
			"Analog reference format fail Trap"
		::= { hxc2000c02v1Traps 115 }

		-- 1.3.6.1.4.1.10106.2.1.1.620401.3
		hxc2000c02v1LockFailTrap NOTIFICATION-TYPE
		OBJECTS { trapCounter, hxc2000c02v1Index, hxc2000c02v1LockFail }
		STATUS current
		DESCRIPTION
			"Reference unlock fail Trap"
		::= { hxc2000c02v1Traps 117 }

		-- 1.3.6.1.4.1.10106.2.1.1.620401.3
		hxc2000c02v1UxcPresTrap NOTIFICATION-TYPE
		OBJECTS { trapCounter, hxc2000c02v1Index, hxc2000c02v1UxcPres }
		STATUS current
		DESCRIPTION
			"UXC2000 presence Trap"
		::= { hxc2000c02v1Traps 119 }

		-- 1.3.6.1.4.1.10106.2.1.1.620401.3
		hxc2000c02v1AudPair0FailTrap NOTIFICATION-TYPE
		OBJECTS { trapCounter, hxc2000c02v1Index, hxc2000c02v1AudPair0Fail }
		STATUS current
		DESCRIPTION
			"Audio pair 0 fail Trap"
		::= { hxc2000c02v1Traps 121 }

		-- 1.3.6.1.4.1.10106.2.1.1.620401.3
		hxc2000c02v1AudPair1FailTrap NOTIFICATION-TYPE
		OBJECTS { trapCounter, hxc2000c02v1Index, hxc2000c02v1AudPair1Fail }
		STATUS current
		DESCRIPTION
			"Audio pair 1 fail Trap"
		::= { hxc2000c02v1Traps 123 }

		-- 1.3.6.1.4.1.10106.2.1.1.620401.3
		hxc2000c02v1AudPair2FailTrap NOTIFICATION-TYPE
		OBJECTS { trapCounter, hxc2000c02v1Index, hxc2000c02v1AudPair2Fail }
		STATUS current
		DESCRIPTION
			"Audio pair 2 fail Trap"
		::= { hxc2000c02v1Traps 125 }

		-- 1.3.6.1.4.1.10106.2.1.1.620401.3
		hxc2000c02v1AudPair3FailTrap NOTIFICATION-TYPE
		OBJECTS { trapCounter, hxc2000c02v1Index, hxc2000c02v1AudPair3Fail }
		STATUS current
		DESCRIPTION
			"Audio pair 3 fail Trap"
		::= { hxc2000c02v1Traps 127 }

		-- 1.3.6.1.4.1.10106.2.1.1.620401.3
		hxc2000c02v1AudPair4FailTrap NOTIFICATION-TYPE
		OBJECTS { trapCounter, hxc2000c02v1Index, hxc2000c02v1AudPair4Fail }
		STATUS current
		DESCRIPTION
			"Audio pair 4 fail Trap"
		::= { hxc2000c02v1Traps 129 }

		-- 1.3.6.1.4.1.10106.2.1.1.620401.3
		hxc2000c02v1AudPair5FailTrap NOTIFICATION-TYPE
		OBJECTS { trapCounter, hxc2000c02v1Index, hxc2000c02v1AudPair5Fail }
		STATUS current
		DESCRIPTION
			"Audio pair 5 fail Trap"
		::= { hxc2000c02v1Traps 131 }

		-- 1.3.6.1.4.1.10106.2.1.1.620401.3
		hxc2000c02v1AudPair6FailTrap NOTIFICATION-TYPE
		OBJECTS { trapCounter, hxc2000c02v1Index, hxc2000c02v1AudPair6Fail }
		STATUS current
		DESCRIPTION
			"Audio pair 6 fail Trap"
		::= { hxc2000c02v1Traps 133 }

		-- 1.3.6.1.4.1.10106.2.1.1.620401.3
		hxc2000c02v1AudPair7FailTrap NOTIFICATION-TYPE
		OBJECTS { trapCounter, hxc2000c02v1Index, hxc2000c02v1AudPair7Fail }
		STATUS current
		DESCRIPTION
			"Audio pair 7 fail Trap"
		::= { hxc2000c02v1Traps 135 }

		-- 1.3.6.1.4.1.10106.2.1.1.620401.3
		hxc2000c02v1InAfdDetctTrap NOTIFICATION-TYPE
		OBJECTS { trapCounter, hxc2000c02v1Index, hxc2000c02v1InAfdDetct }
		STATUS current
		DESCRIPTION
			"Input detected AFD Trap"
		::= { hxc2000c02v1Traps 137 }

		-- 1.3.6.1.4.1.10106.2.1.1.620401.3
		hxc2000c02v1InCfDetctTrap NOTIFICATION-TYPE
		OBJECTS { trapCounter, hxc2000c02v1Index, hxc2000c02v1InCfDetct }
		STATUS current
		DESCRIPTION
			"Input detected coded frame Trap"
		::= { hxc2000c02v1Traps 139 }

		-- 1.3.6.1.4.1.10106.2.1.1.620401.3
		hxc2000c02v1InFormatTrap NOTIFICATION-TYPE
		OBJECTS { trapCounter, hxc2000c02v1Index, hxc2000c02v1InFormat }
		STATUS current
		DESCRIPTION
			"Input format Trap"
		::= { hxc2000c02v1Traps 141 }

		-- 1.3.6.1.4.1.10106.2.1.1.620401.3
		hxc2000c02v1RefFormatTrap NOTIFICATION-TYPE
		OBJECTS { trapCounter, hxc2000c02v1Index, hxc2000c02v1RefFormat }
		STATUS current
		DESCRIPTION
			"Reference format Trap"
		::= { hxc2000c02v1Traps 143 }

		-- 1.3.6.1.4.1.10106.2.1.1.620401.3
		hxc2000c02v1TxFormatTrap NOTIFICATION-TYPE
		OBJECTS { trapCounter, hxc2000c02v1Index, hxc2000c02v1TxFormat }
		STATUS current
		DESCRIPTION
			"Output format Trap"
		::= { hxc2000c02v1Traps 145 }

		-- 1.3.6.1.4.1.10106.2.1.1.623301
		mpx2000c01v1Traps OBJECT IDENTIFIER ::= { albalaTraps 623301 }

		-- 1.3.6.1.4.1.10106.2.1.1.623301.3
		mpx2000c01v1AudioMpxNTrap NOTIFICATION-TYPE
		OBJECTS { trapCounter, mpx2000c01v1Index, mpx2000c01v1AudioMpxN }
		STATUS current
		DESCRIPTION
			"Inserts audio Trap"
		::= { mpx2000c01v1Traps 3 }

		-- 1.3.6.1.4.1.10106.2.1.1.623301.3
		mpx2000c01v1ControlTrap NOTIFICATION-TYPE
		OBJECTS { trapCounter, mpx2000c01v1Index, mpx2000c01v1Control }
		STATUS current
		DESCRIPTION
			"Control mode Trap"
		::= { mpx2000c01v1Traps 5 }

		-- 1.3.6.1.4.1.10106.2.1.1.623301.3
		mpx2000c01v1MpxFailTrap NOTIFICATION-TYPE
		OBJECTS { trapCounter, mpx2000c01v1Index, mpx2000c01v1MpxFail }
		STATUS current
		DESCRIPTION
			"MPX signal absence Trap"
		::= { mpx2000c01v1Traps 15 }

		-- 1.3.6.1.4.1.10106.2.1.1.623301.3
		mpx2000c01v1AudFailTrap NOTIFICATION-TYPE
		OBJECTS { trapCounter, mpx2000c01v1Index, mpx2000c01v1AudFail }
		STATUS current
		DESCRIPTION
			"AUD signal absence Trap"
		::= { mpx2000c01v1Traps 17 }

		-- 1.3.6.1.4.1.10106.2.1.1.623301.3
		mpx2000c01v1GpiTrap NOTIFICATION-TYPE
		OBJECTS { trapCounter, mpx2000c01v1Index, mpx2000c01v1Gpi }
		STATUS current
		DESCRIPTION
			"GPI Trap"
		::= { mpx2000c01v1Traps 19 }

		-- 1.3.6.1.4.1.10106.2.1.1.627101
		rfa2018c01v1Traps OBJECT IDENTIFIER ::= { albalaTraps 627101 }

		-- 1.3.6.1.4.1.10106.2.1.1.627101.3
		rfa2018c01v1VoltFailTrap NOTIFICATION-TYPE
		OBJECTS { trapCounter, rfa2018c01v1Index, rfa2018c01v1VoltFail }
		STATUS current
		DESCRIPTION
			"Indicates that actual votage is out of recommended range Trap"
		::= { rfa2018c01v1Traps 19 }

		-- 1.3.6.1.4.1.10106.2.1.1.627101.3
		rfa2018c01v1CurrFailTrap NOTIFICATION-TYPE
		OBJECTS { trapCounter, rfa2018c01v1Index, rfa2018c01v1CurrFail }
		STATUS current
		DESCRIPTION
			"Indicates that actual current is out of recommended range Trap"
		::= { rfa2018c01v1Traps 21 }

		-- 1.3.6.1.4.1.10106.2.1.1.627101.3
		rfa2018c01v1TempFailTrap NOTIFICATION-TYPE
		OBJECTS { trapCounter, rfa2018c01v1Index, rfa2018c01v1TempFail }
		STATUS current
		DESCRIPTION
			"Indicates that actual temperature is over recommended range Trap"
		::= { rfa2018c01v1Traps 23 }

		
--  1.3.6.1.4.1.10106.2.1.1.1
		-- 1.3.6.1.4.1.10106.2.1.2
		trapCounter OBJECT-TYPE
			SYNTAX Integer32
			MAX-ACCESS read-only
			STATUS current
			DESCRIPTION
				"OID of the signal whose change of status is being notified."
			::= { albalaObjects 2 }

		
		-- 1.3.6.1.4.1.10106.2.1.3
		agentStatus OBJECT-TYPE
			SYNTAX AgentSts
			MAX-ACCESS read-only
			STATUS current
			DESCRIPTION
				"Agent status comunication"
			::= { albalaObjects 3 }


		-- 1.3.6.1.4.1.10106.2.1.4
		versionKernel OBJECT-TYPE
			SYNTAX Integer32
			MAX-ACCESS read-write
			STATUS current
			DESCRIPTION
				"Version Kernel"
			::= { albalaObjects 4 }

		
		-- 1.3.6.1.4.1.10106.2.1.5
		versionRootfs OBJECT-TYPE
			SYNTAX Integer32
			MAX-ACCESS read-write
			STATUS current
			DESCRIPTION
				"Version Root file system"
			::= { albalaObjects 5 }

		
		-- 1.3.6.1.4.1.10106.2.1.6
		versionTle3001 OBJECT-TYPE
			SYNTAX Integer32
			MAX-ACCESS read-write
			STATUS current
			DESCRIPTION
				"Version programs TLE3001"
			::= { albalaObjects 6 }

		
		-- 1.3.6.1.4.1.10106.2.1.7
		versionParameters OBJECT-TYPE
			SYNTAX Integer32
			MAX-ACCESS read-write
			STATUS current
			DESCRIPTION
				"Version File parameters"
			::= { albalaObjects 7 }

		
--  1.3.6.1.4.1.10106.2.3
		-- 1.3.6.1.4.1.10106.2.3
		albalaConformance OBJECT IDENTIFIER ::= { albalaGeneric 3 }

		
--  1.3.6.1.4.1.10106.2.3.1
		-- 1.3.6.1.4.1.10106.2.3.1
		varGroups OBJECT IDENTIFIER ::= { albalaConformance 1 }

		
		-- 1.3.6.1.4.1.10106.2.2.1.1
		genGroup OBJECT-GROUP
			OBJECTS { trapCounter, agentStatus, versionKernel, versionRootfs, versionTle3001, 
				versionParameters }
			STATUS current
			DESCRIPTION 
				"Geniric group"
			::= { varGroups 1 }

		
		-- 1.3.6.1.4.1.10106.2.3.1.2
		moduleGroup OBJECT-GROUP
			OBJECTS { moduleIndex, moduleTrapEnable, moduleExpectedType, moduleFoundType, moduleStatus
				 }
			STATUS current
			DESCRIPTION 
				"Module group"
			::= { varGroups 2 }


		-- 1.3.6.1.4.1.10106.2.3.1.89101
		dvp3222p01v1ModuleGroup OBJECT-GROUP
			OBJECTS {dvp3222p01v1Index, dvp3222p01v1Output1, dvp3222p01v1Output2, dvp3222p01v1SwitchTime, dvp3222p01v1NoSync, 
				dvp3222p01v1SyncLines }
			STATUS current
			DESCRIPTION
				"Module DVP3222P01V1 Group"
			::= { varGroups 89101 }

		-- 1.3.6.1.4.1.10106.2.3.1.125101
		vct3000p01v1ModuleGroup OBJECT-GROUP
			OBJECTS {vct3000p01v1Index, vct3000p01v1Mode, vct3000p01v1ModeTrapEnable, vct3000p01v1Input, vct3000p01v1InputTrapEnable, 
				vct3000p01v1Gpi0, vct3000p01v1Gpi1, vct3000p01v1MainFail, vct3000p01v1MainFailTrapEnable, vct3000p01v1ResFail, 
				vct3000p01v1ResFailTrapEnable }
			STATUS current
			DESCRIPTION
				"Module VCT3000P01V1 Group"
			::= { varGroups 125101 }

		-- 1.3.6.1.4.1.10106.2.3.1.126001
		vct3000c02v1ModuleGroup OBJECT-GROUP
			OBJECTS {vct3000c02v1Index, vct3000c02v1Mode, vct3000c02v1ModeTrapEnable, vct3000c02v1Input, vct3000c02v1InputTrapEnable, 
				vct3000c02v1Gpi0, vct3000c02v1Gpi1, vct3000c02v1MainFail, vct3000c02v1MainFailTrapEnable, vct3000c02v1ResFail, 
				vct3000c02v1ResFailTrapEnable }
			STATUS current
			DESCRIPTION
				"Module VCT3000C02V1 Group"
			::= { varGroups 126001 }

		-- 1.3.6.1.4.1.10106.2.3.1.126201
		vct3000c04v1ModuleGroup OBJECT-GROUP
			OBJECTS {vct3000c04v1Index, vct3000c04v1Mode, vct3000c04v1ModeTrapEnable, vct3000c04v1Input, vct3000c04v1InputTrapEnable, 
				vct3000c04v1Gpi0, vct3000c04v1Gpi1, vct3000c04v1MainFail, vct3000c04v1MainFailTrapEnable, vct3000c04v1ResFail, 
				vct3000c04v1ResFailTrapEnable }
			STATUS current
			DESCRIPTION
				"Module VCT3000C04V1 Group"
			::= { varGroups 126201 }

		-- 1.3.6.1.4.1.10106.2.3.1.126301
		vct3000c05v1ModuleGroup OBJECT-GROUP
			OBJECTS {vct3000c05v1Index, vct3000c05v1Mode, vct3000c05v1ModeTrapEnable, vct3000c05v1Input, vct3000c05v1InputTrapEnable, 
				vct3000c05v1Gpi0, vct3000c05v1Gpi1, vct3000c05v1MainFail, vct3000c05v1MainFailTrapEnable, vct3000c05v1ResFail, 
				vct3000c05v1ResFailTrapEnable }
			STATUS current
			DESCRIPTION
				"Module VCT3000C05V1 Group"
			::= { varGroups 126301 }

		-- 1.3.6.1.4.1.10106.2.3.1.128301
		dvm3000p01v1ModuleGroup OBJECT-GROUP
			OBJECTS {dvm3000p01v1Index, dvm3000p01v1Chroma, dvm3000p01v1LowPassFilter, dvm3000p01v1VbiPass, dvm3000p01v1Mode, 
				dvm3000p01v1NoSigA, dvm3000p01v1NoSigATrapEnable, dvm3000p01v1MaxEqA, dvm3000p01v1NoSigB, dvm3000p01v1NoSigBTrapEnable, 
				dvm3000p01v1MaxEqB }
			STATUS current
			DESCRIPTION
				"Module DVM3000P01V1 Group"
			::= { varGroups 128301 }

		-- 1.3.6.1.4.1.10106.2.3.1.128701
		tpg3000p01v1ModuleGroup OBJECT-GROUP
			OBJECTS {tpg3000p01v1Index, tpg3000p01v1ColourBars, tpg3000p01v1Text, tpg3000p01v1Lines, tpg3000p01v1Char1, 
				tpg3000p01v1Char2, tpg3000p01v1Char3, tpg3000p01v1Char4, tpg3000p01v1Char5, tpg3000p01v1Char6, 
				tpg3000p01v1Char7, tpg3000p01v1Char8, tpg3000p01v1TextForeColour, tpg3000p01v1TextBackColour }
			STATUS current
			DESCRIPTION
				"Module TPG3000P01V1 Group"
			::= { varGroups 128701 }

		-- 1.3.6.1.4.1.10106.2.3.1.129101
		dsw3000p01v1ModuleGroup OBJECT-GROUP
			OBJECTS {dsw3000p01v1Index, dsw3000p01v1Mode, dsw3000p01v1ModeTrapEnable, dsw3000p01v1Buzzer, dsw3000p01v1Input, 
				dsw3000p01v1InputTrapEnable, dsw3000p01v1MainFail, dsw3000p01v1MainFailTrapEnable, dsw3000p01v1ExtMainFail, dsw3000p01v1ExtMainFailTrapEnable, 
				dsw3000p01v1ResFail, dsw3000p01v1ResFailTrapEnable, dsw3000p01v1ExtResFail, dsw3000p01v1ExtResFailTrapEnable, dsw3000p01v1AuxFail, 
				dsw3000p01v1AuxFailTrapEnable, dsw3000p01v1ExtAuxFail, dsw3000p01v1ExtAuxFailTrapEnable }
			STATUS current
			DESCRIPTION
				"Module DSW3000P01V1 Group"
			::= { varGroups 129101 }

		-- 1.3.6.1.4.1.10106.2.3.1.130101
		lns3000p01v1ModuleGroup OBJECT-GROUP
			OBJECTS {lns3000p01v1Index, lns3000p01v1LumaGain, lns3000p01v1ChromaGain, lns3000p01v1BlackOffset, lns3000p01v1Mode, 
				lns3000p01v1SyncOut, lns3000p01v1NoSignalPgm, lns3000p01v1NoSignalPgmTrapEnable, lns3000p01v1EdhChkPgm, lns3000p01v1TimingErr, 
				lns3000p01v1TimingErrTrapEnable, lns3000p01v1NoSignalRef, lns3000p01v1NoSignalRefTrapEnable, lns3000p01v1EdhChkRef }
			STATUS current
			DESCRIPTION
				"Module LNS3000P01V1 Group"
			::= { varGroups 130101 }

		-- 1.3.6.1.4.1.10106.2.3.1.131502
		dli3000p01v2ModuleGroup OBJECT-GROUP
			OBJECTS {dli3000p01v2Index, dli3000p01v2LogoSdi, dli3000p01v2LogoCcvs, dli3000p01v2LoadLogo, dli3000p01v2SelectedLogo, 
				dli3000p01v2FadeTime, dli3000p01v2LogoPosH, dli3000p01v2LogoSizeH, dli3000p01v2LogoPosV, dli3000p01v2LogoSizeV, 
				dli3000p01v2LogoMemSize, dli3000p01v2MaxEq, dli3000p01v2NoSig, dli3000p01v2NoSigTrapEnable }
			STATUS current
			DESCRIPTION
				"Module DLI3000P01V2 Group"
			::= { varGroups 131502 }

		-- 1.3.6.1.4.1.10106.2.3.1.133501
		tly3032p01v1ModuleGroup OBJECT-GROUP
			OBJECTS {tly3032p01v1Index, tly3032p01v1Gpi1, tly3032p01v1Gpi1TrapEnable, tly3032p01v1Gpi2, tly3032p01v1Gpi2TrapEnable, 
				tly3032p01v1Gpi3, tly3032p01v1Gpi3TrapEnable, tly3032p01v1Gpi4, tly3032p01v1Gpi4TrapEnable, tly3032p01v1Gpi5, 
				tly3032p01v1Gpi5TrapEnable, tly3032p01v1Gpi6, tly3032p01v1Gpi6TrapEnable, tly3032p01v1Gpi7, tly3032p01v1Gpi7TrapEnable, 
				tly3032p01v1Gpi8, tly3032p01v1Gpi8TrapEnable, tly3032p01v1Gpi9, tly3032p01v1Gpi9TrapEnable, tly3032p01v1Gpi10, 
				tly3032p01v1Gpi10TrapEnable, tly3032p01v1Gpi11, tly3032p01v1Gpi11TrapEnable, tly3032p01v1Gpi12, tly3032p01v1Gpi12TrapEnable, 
				tly3032p01v1Gpi13, tly3032p01v1Gpi13TrapEnable, tly3032p01v1Gpi14, tly3032p01v1Gpi14TrapEnable, tly3032p01v1Gpi15, 
				tly3032p01v1Gpi15TrapEnable, tly3032p01v1Gpi16, tly3032p01v1Gpi16TrapEnable, tly3032p01v1Gpi17, tly3032p01v1Gpi17TrapEnable, 
				tly3032p01v1Gpi18, tly3032p01v1Gpi18TrapEnable, tly3032p01v1Gpi19, tly3032p01v1Gpi19TrapEnable, tly3032p01v1Gpi20, 
				tly3032p01v1Gpi20TrapEnable, tly3032p01v1Gpi21, tly3032p01v1Gpi21TrapEnable, tly3032p01v1Gpi22, tly3032p01v1Gpi22TrapEnable, 
				tly3032p01v1Gpi23, tly3032p01v1Gpi23TrapEnable, tly3032p01v1Gpi24, tly3032p01v1Gpi24TrapEnable, tly3032p01v1Gpi25, 
				tly3032p01v1Gpi25TrapEnable, tly3032p01v1Gpi26, tly3032p01v1Gpi26TrapEnable, tly3032p01v1Gpi27, tly3032p01v1Gpi27TrapEnable, 
				tly3032p01v1Gpi28, tly3032p01v1Gpi28TrapEnable, tly3032p01v1Gpi29, tly3032p01v1Gpi29TrapEnable, tly3032p01v1Gpi30, 
				tly3032p01v1Gpi30TrapEnable, tly3032p01v1Gpi31, tly3032p01v1Gpi31TrapEnable, tly3032p01v1Gpi32, tly3032p01v1Gpi32TrapEnable }
			STATUS current
			DESCRIPTION
				"Module TLY3032P01V1 Group"
			::= { varGroups 133501 }

		-- 1.3.6.1.4.1.10106.2.3.1.133901
		tly3016p01v1ModuleGroup OBJECT-GROUP
			OBJECTS {tly3016p01v1Index, tly3016p01v1Gpo1, tly3016p01v1Gpo2, tly3016p01v1Gpo3, tly3016p01v1Gpo4, 
				tly3016p01v1Gpo5, tly3016p01v1Gpo6, tly3016p01v1Gpo7, tly3016p01v1Gpo8, tly3016p01v1Gpo9, 
				tly3016p01v1Gpo10, tly3016p01v1Gpo11, tly3016p01v1Gpo12, tly3016p01v1Gpo13, tly3016p01v1Gpo14, 
				tly3016p01v1Gpo15, tly3016p01v1Gpo16 }
			STATUS current
			DESCRIPTION
				"Module TLY3016P01V1 Group"
			::= { varGroups 133901 }

		-- 1.3.6.1.4.1.10106.2.3.1.134801
		aac3000p01v1ModuleGroup OBJECT-GROUP
			OBJECTS {aac3000p01v1Index, aac3000p01v1Bits, aac3000p01v1Silence, aac3000p01v1Mode, aac3000p01v1InputRef, 
				aac3000p01v1OutputFreq, aac3000p01v1OvlLevel, aac3000p01v1NoVid, aac3000p01v1NoVidTrapEnable, aac3000p01v1NoAes, 
				aac3000p01v1NoAesTrapEnable, aac3000p01v1NoWclk, aac3000p01v1NoWclkTrapEnable, aac3000p01v1Unlock, aac3000p01v1UnlockTrapEnable, 
				aac3000p01v1OvldS1Cha, aac3000p01v1OvldS1ChaTrapEnable, aac3000p01v1OvldS1Chb, aac3000p01v1OvldS1ChbTrapEnable, aac3000p01v1OvldS2Cha, 
				aac3000p01v1OvldS2ChaTrapEnable, aac3000p01v1OvldS2Chb, aac3000p01v1OvldS2ChbTrapEnable, aac3000p01v1AesDetFreq, aac3000p01v1WclkDetFreq, 
				aac3000p01v1Det525, aac3000p01v1Det625 }
			STATUS current
			DESCRIPTION
				"Module AAC3000P01V1 Group"
			::= { varGroups 134801 }

		-- 1.3.6.1.4.1.10106.2.3.1.134901
		aem3000p01v1ModuleGroup OBJECT-GROUP
			OBJECTS {aem3000p01v1Index, aem3000p01v1EmbedIns, aem3000p01v1EmbedMode, aem3000p01v1EmbedCh, aem3000p01v1EmbedBits, 
				aem3000p01v1Group, aem3000p01v1GroupTrapEnable, aem3000p01v1GainAes1A, aem3000p01v1PhaseAes1A, aem3000p01v1GainAes1B, 
				aem3000p01v1PhaseAes1B, aem3000p01v1GainAes2A, aem3000p01v1PhaseAes2A, aem3000p01v1GainAes2B, aem3000p01v1PhaseAes2B, 
				aem3000p01v1Aes1AInput, aem3000p01v1Aes1BInput, aem3000p01v1Aes2AInput, aem3000p01v1Aes2BInput, aem3000p01v1OverloadLevel, 
				aem3000p01v1SilenceLevel, aem3000p01v1SilenceTime, aem3000p01v1NoSignal, aem3000p01v1NoSignalTrapEnable, aem3000p01v1SilOut1, 
				aem3000p01v1SilOut1TrapEnable, aem3000p01v1SilOut2, aem3000p01v1SilOut2TrapEnable, aem3000p01v1OvlOut1, aem3000p01v1OvlOut1TrapEnable, 
				aem3000p01v1OvlOut2, aem3000p01v1OvlOut2TrapEnable, aem3000p01v1PckAGr1, aem3000p01v1PckAGr2, aem3000p01v1PckAGr3, 
				aem3000p01v1PckAGr4 }
			STATUS current
			DESCRIPTION
				"Module AEM3000P01V1 Group"
			::= { varGroups 134901 }

		-- 1.3.6.1.4.1.10106.2.3.1.135801
		ade3000p01v1ModuleGroup OBJECT-GROUP
			OBJECTS {ade3000p01v1Index, ade3000p01v1Group, ade3000p01v1GroupTrapEnable, ade3000p01v1GainAes1A, ade3000p01v1PhaseAes1A, 
				ade3000p01v1GainAes1B, ade3000p01v1PhaseAes1B, ade3000p01v1GainAes2A, ade3000p01v1PhaseAes2A, ade3000p01v1GainAes2B, 
				ade3000p01v1PhaseAes2B, ade3000p01v1Aes1AInput, ade3000p01v1Aes1BInput, ade3000p01v1Aes2AInput, ade3000p01v1Aes2BInput, 
				ade3000p01v1MonoOut1, ade3000p01v1MonoOut2, ade3000p01v1MuteOut1, ade3000p01v1MuteOut2, ade3000p01v1OverloadLevel, 
				ade3000p01v1SilenceLevel, ade3000p01v1SilenceTime, ade3000p01v1ClnGr1, ade3000p01v1ClnGr2, ade3000p01v1ClnGr3, 
				ade3000p01v1ClnGr4, ade3000p01v1NoSignal, ade3000p01v1NoSignalTrapEnable, ade3000p01v1NsamAes1, ade3000p01v1NsamAes1TrapEnable, 
				ade3000p01v1NsamAes2, ade3000p01v1NsamAes2TrapEnable, ade3000p01v1SilOut1, ade3000p01v1SilOut1TrapEnable, ade3000p01v1SilOut2, 
				ade3000p01v1SilOut2TrapEnable, ade3000p01v1OvlOut1, ade3000p01v1OvlOut1TrapEnable, ade3000p01v1OvlOut2, ade3000p01v1OvlOut2TrapEnable, 
				ade3000p01v1PckAGr1, ade3000p01v1PckAGr2, ade3000p01v1PckAGr3, ade3000p01v1PckAGr4 }
			STATUS current
			DESCRIPTION
				"Module ADE3000P01V1 Group"
			::= { varGroups 135801 }

		-- 1.3.6.1.4.1.10106.2.3.1.136301
		dsw3000c02v1ModuleGroup OBJECT-GROUP
			OBJECTS {dsw3000c02v1Index, dsw3000c02v1Mode, dsw3000c02v1ModeTrapEnable, dsw3000c02v1Buzzer, dsw3000c02v1Input, 
				dsw3000c02v1InputTrapEnable, dsw3000c02v1MainFail, dsw3000c02v1MainFailTrapEnable, dsw3000c02v1ExtMainFail, dsw3000c02v1ExtMainFailTrapEnable, 
				dsw3000c02v1ResFail, dsw3000c02v1ResFailTrapEnable, dsw3000c02v1ExtResFail, dsw3000c02v1ExtResFailTrapEnable, dsw3000c02v1AuxFail, 
				dsw3000c02v1AuxFailTrapEnable, dsw3000c02v1ExtAuxFail, dsw3000c02v1ExtAuxFailTrapEnable }
			STATUS current
			DESCRIPTION
				"Module DSW3000C02V1 Group"
			::= { varGroups 136301 }

		-- 1.3.6.1.4.1.10106.2.3.1.136601
		dem3000p01v1ModuleGroup OBJECT-GROUP
			OBJECTS {dem3000p01v1Index, dem3000p01v1EmbedInsA, dem3000p01v1EmbedModeA, dem3000p01v1EmbedChA, dem3000p01v1EmbedInsB, 
				dem3000p01v1EmbedModeB, dem3000p01v1EmbedChB, dem3000p01v1EmbedBits, dem3000p01v1OperatingMode, dem3000p01v1GroupA, 
				dem3000p01v1GroupATrapEnable, dem3000p01v1GroupB, dem3000p01v1GroupBTrapEnable, dem3000p01v1NoSignalA, dem3000p01v1NoSignalATrapEnable, 
				dem3000p01v1NoAes1A, dem3000p01v1NoAes1ATrapEnable, dem3000p01v1UlckAes1A, dem3000p01v1UlckAes1ATrapEnable, dem3000p01v1NoAes2A, 
				dem3000p01v1NoAes2ATrapEnable, dem3000p01v1UlckAes2A, dem3000p01v1UlckAes2ATrapEnable, dem3000p01v1PckAGr1A, dem3000p01v1PckAGr2A, 
				dem3000p01v1PckAGr3A, dem3000p01v1PckAGr4A, dem3000p01v1NoSignalB, dem3000p01v1NoSignalBTrapEnable, dem3000p01v1NoAes1B, 
				dem3000p01v1NoAes1BTrapEnable, dem3000p01v1UlckAes1B, dem3000p01v1UlckAes1BTrapEnable, dem3000p01v1NoAes2B, dem3000p01v1NoAes2BTrapEnable, 
				dem3000p01v1UlckAes2B, dem3000p01v1UlckAes2BTrapEnable, dem3000p01v1PckAGr1B, dem3000p01v1PckAGr2B, dem3000p01v1PckAGr3B, 
				dem3000p01v1PckAGr4B }
			STATUS current
			DESCRIPTION
				"Module DEM3000P01V1 Group"
			::= { varGroups 136601 }

		-- 1.3.6.1.4.1.10106.2.3.1.137101
		dde3000p01v1ModuleGroup OBJECT-GROUP
			OBJECTS {dde3000p01v1Index, dde3000p01v1OperatingMode, dde3000p01v1GroupA, dde3000p01v1GroupATrapEnable, dde3000p01v1GroupB, 
				dde3000p01v1GroupBTrapEnable, dde3000p01v1ClnGr1A, dde3000p01v1ClnGr2A, dde3000p01v1ClnGr3A, dde3000p01v1ClnGr4A, 
				dde3000p01v1ClnGr1B, dde3000p01v1ClnGr2B, dde3000p01v1ClnGr3B, dde3000p01v1ClnGr4B, dde3000p01v1MuteAes1A, 
				dde3000p01v1PhInvAes1A, dde3000p01v1SwapAes1A, dde3000p01v1MuteAes2A, dde3000p01v1PhInvAes2A, dde3000p01v1SwapAes2A, 
				dde3000p01v1SwapAesA, dde3000p01v1MuteAes1B, dde3000p01v1PhInvAes1B, dde3000p01v1SwapAes1B, dde3000p01v1MuteAes2B, 
				dde3000p01v1PhInvAes2B, dde3000p01v1SwapAes2B, dde3000p01v1SwapAesB, dde3000p01v1NoSignalA, dde3000p01v1NoSignalATrapEnable, 
				dde3000p01v1NsamAes1A, dde3000p01v1NsamAes1ATrapEnable, dde3000p01v1NsamAes2A, dde3000p01v1NsamAes2ATrapEnable, dde3000p01v1PckAGr1A, 
				dde3000p01v1PckAGr2A, dde3000p01v1PckAGr3A, dde3000p01v1PckAGr4A, dde3000p01v1NoSignalB, dde3000p01v1NoSignalBTrapEnable, 
				dde3000p01v1NsamAes1B, dde3000p01v1NsamAes1BTrapEnable, dde3000p01v1NsamAes2B, dde3000p01v1NsamAes2BTrapEnable, dde3000p01v1PckAGr1B, 
				dde3000p01v1PckAGr2B, dde3000p01v1PckAGr3B, dde3000p01v1PckAGr4B }
			STATUS current
			DESCRIPTION
				"Module DDE3000P01V1 Group"
			::= { varGroups 137101 }

		-- 1.3.6.1.4.1.10106.2.3.1.137701
		avp0621p01v1ModuleGroup OBJECT-GROUP
			OBJECTS {avp0621p01v1Index, avp0621p01v1Output1, avp0621p01v1SwitchMode, avp0621p01v1SwitchTime, avp0621p01v1NoSync, 
				avp0621p01v1SyncLines, avp0621p01v1SyncType }
			STATUS current
			DESCRIPTION
				"Module AVP0621P01V1 Group"
			::= { varGroups 137701 }

		-- 1.3.6.1.4.1.10106.2.3.1.139701
		aad3034p01v1ModuleGroup OBJECT-GROUP
			OBJECTS {aad3034p01v1Index, aad3034p01v1GainRA, aad3034p01v1GainLA, aad3034p01v1GainRB, aad3034p01v1GainLB, 
				aad3034p01v1GainRRlA, aad3034p01v1GainLRlA, aad3034p01v1GainRRlB, aad3034p01v1GainLRlB, aad3034p01v1NoSigTout, 
				aad3034p01v1SilThrLevel, aad3034p01v1OvlThrLevel, aad3034p01v1SilenceRA, aad3034p01v1SilenceRATrapEnable, aad3034p01v1SilenceLA, 
				aad3034p01v1SilenceLATrapEnable, aad3034p01v1AntiphaseA, aad3034p01v1AntiphaseATrapEnable, aad3034p01v1OverloadRA, aad3034p01v1OverloadRATrapEnable, 
				aad3034p01v1OverloadLA, aad3034p01v1OverloadLATrapEnable, aad3034p01v1OverloadRlA, aad3034p01v1OverloadRlATrapEnable, aad3034p01v1SilenceRB, 
				aad3034p01v1SilenceRBTrapEnable, aad3034p01v1SilenceLB, aad3034p01v1SilenceLBTrapEnable, aad3034p01v1AntiphaseB, aad3034p01v1AntiphaseBTrapEnable, 
				aad3034p01v1OverloadRB, aad3034p01v1OverloadRBTrapEnable, aad3034p01v1OverloadLB, aad3034p01v1OverloadLBTrapEnable, aad3034p01v1OverloadRlB, 
				aad3034p01v1OverloadRlBTrapEnable, aad3034p01v1LevelRA, aad3034p01v1LevelLA, aad3034p01v1LevelRB, aad3034p01v1LevelLB }
			STATUS current
			DESCRIPTION
				"Module AAD3034P01V1 Group"
			::= { varGroups 139701 }

		-- 1.3.6.1.4.1.10106.2.3.1.140401
		avp1221p01v1ModuleGroup OBJECT-GROUP
			OBJECTS {avp1221p01v1Index, avp1221p01v1Output1, avp1221p01v1SwitchMode, avp1221p01v1SwitchTime, avp1221p01v1NoSync, 
				avp1221p01v1SyncLines, avp1221p01v1SyncType }
			STATUS current
			DESCRIPTION
				"Module AVP1221P01V1 Group"
			::= { varGroups 140401 }

		-- 1.3.6.1.4.1.10106.2.3.1.140801
		aap1221p01v1ModuleGroup OBJECT-GROUP
			OBJECTS {aap1221p01v1Index, aap1221p01v1Output1, aap1221p01v1SwitchMode }
			STATUS current
			DESCRIPTION
				"Module AAP1221P01V1 Group"
			::= { varGroups 140801 }

		-- 1.3.6.1.4.1.10106.2.3.1.141201
		frs3000p01v1ModuleGroup OBJECT-GROUP
			OBJECTS {frs3000p01v1Index, frs3000p01v1Lines, frs3000p01v1FailMode, frs3000p01v1FreezeMode, frs3000p01v1LumaFilter, 
				frs3000p01v1OperMode, frs3000p01v1SubcarrMode, frs3000p01v1SynchroMode, frs3000p01v1HDelay, frs3000p01v1HDelayFine, 
				frs3000p01v1VDelay, frs3000p01v1LumaGain, frs3000p01v1ChromaGain, frs3000p01v1BlackOffset, frs3000p01v1SubcarrOffset, 
				frs3000p01v1NoRef, frs3000p01v1NoRefTrapEnable, frs3000p01v1RefUnlock, frs3000p01v1RefUnlockTrapEnable, frs3000p01v1NoSig, 
				frs3000p01v1NoSigTrapEnable, frs3000p01v1SubcarrUnlock, frs3000p01v1SubcarrUnlockTrapEnable, frs3000p01v1EdhError, frs3000p01v1SdiFormat, 
				frs3000p01v1RefFormat }
			STATUS current
			DESCRIPTION
				"Module FRS3000P01V1 Group"
			::= { varGroups 141201 }

		-- 1.3.6.1.4.1.10106.2.3.1.141701
		pds3000p01v1ModuleGroup OBJECT-GROUP
			OBJECTS {pds3000p01v1Index, pds3000p01v1Lines, pds3000p01v1VbiMode, pds3000p01v1FailMode, pds3000p01v1DecoderMode, 
				pds3000p01v1OperMode, pds3000p01v1HDelay, pds3000p01v1VDelay, pds3000p01v1LumaGain, pds3000p01v1ChromaGain, 
				pds3000p01v1BlackOffset, pds3000p01v1Hue, pds3000p01v1EqualLength, pds3000p01v1NoRef, pds3000p01v1NoRefTrapEnable, 
				pds3000p01v1RefUnlock, pds3000p01v1RefUnlockTrapEnable, pds3000p01v1NoCcvs, pds3000p01v1NoCcvsTrapEnable, pds3000p01v1CcvsUnlock, 
				pds3000p01v1CcvsUnlockTrapEnable, pds3000p01v1DecOvld, pds3000p01v1DecOvldTrapEnable, pds3000p01v1EqualOvld, pds3000p01v1AdOvld, 
				pds3000p01v1AdOvldTrapEnable }
			STATUS current
			DESCRIPTION
				"Module PDS3000P01V1 Group"
			::= { varGroups 141701 }

		-- 1.3.6.1.4.1.10106.2.3.1.143301
		avp1222p01v1ModuleGroup OBJECT-GROUP
			OBJECTS {avp1222p01v1Index, avp1222p01v1Output1, avp1222p01v1Output2, avp1222p01v1SwitchMode, avp1222p01v1SwitchTime, 
				avp1222p01v1NoSync, avp1222p01v1SyncLines, avp1222p01v1SyncType }
			STATUS current
			DESCRIPTION
				"Module AVP1222P01V1 Group"
			::= { varGroups 143301 }

		-- 1.3.6.1.4.1.10106.2.3.1.145201
		aap0622p01v1ModuleGroup OBJECT-GROUP
			OBJECTS {aap0622p01v1Index, aap0622p01v1Output1, aap0622p01v1Output2, aap0622p01v1SwitchMode }
			STATUS current
			DESCRIPTION
				"Module AAP0622P01V1 Group"
			::= { varGroups 145201 }

		-- 1.3.6.1.4.1.10106.2.3.1.145601
		avp0622p01v1ModuleGroup OBJECT-GROUP
			OBJECTS {avp0622p01v1Index, avp0622p01v1Output1, avp0622p01v1Output2, avp0622p01v1SwitchMode, avp0622p01v1SwitchTime, 
				avp0622p01v1NoSync, avp0622p01v1SyncLines, avp0622p01v1SyncType }
			STATUS current
			DESCRIPTION
				"Module AVP0622P01V1 Group"
			::= { varGroups 145601 }

		-- 1.3.6.1.4.1.10106.2.3.1.147801
		aad3024p01v1ModuleGroup OBJECT-GROUP
			OBJECTS {aad3024p01v1Index, aad3024p01v1GainRA, aad3024p01v1GainLA, aad3024p01v1GainRB, aad3024p01v1GainLB, 
				aad3024p01v1NoSigTout, aad3024p01v1SilThrLevel, aad3024p01v1OvlThrLevel, aad3024p01v1SilenceRA, aad3024p01v1SilenceRATrapEnable, 
				aad3024p01v1SilenceLA, aad3024p01v1SilenceLATrapEnable, aad3024p01v1AntiphaseA, aad3024p01v1AntiphaseATrapEnable, aad3024p01v1OverloadRA, 
				aad3024p01v1OverloadRATrapEnable, aad3024p01v1OverloadLA, aad3024p01v1OverloadLATrapEnable, aad3024p01v1SilenceRB, aad3024p01v1SilenceRBTrapEnable, 
				aad3024p01v1SilenceLB, aad3024p01v1SilenceLBTrapEnable, aad3024p01v1AntiphaseB, aad3024p01v1AntiphaseBTrapEnable, aad3024p01v1OverloadRB, 
				aad3024p01v1OverloadRBTrapEnable, aad3024p01v1OverloadLB, aad3024p01v1OverloadLBTrapEnable, aad3024p01v1LevelRA, aad3024p01v1LevelLA, 
				aad3024p01v1LevelRB, aad3024p01v1LevelLB }
			STATUS current
			DESCRIPTION
				"Module AAD3024P01V1 Group"
			::= { varGroups 147801 }

		-- 1.3.6.1.4.1.10106.2.3.1.147901
		aad3014p01v1ModuleGroup OBJECT-GROUP
			OBJECTS {aad3014p01v1Index, aad3014p01v1GainR, aad3014p01v1GainL, aad3014p01v1NoSigTout, aad3014p01v1SilThrLevel, 
				aad3014p01v1OvlThrLevel, aad3014p01v1SilenceR, aad3014p01v1SilenceRTrapEnable, aad3014p01v1SilenceL, aad3014p01v1SilenceLTrapEnable, 
				aad3014p01v1Antiphase, aad3014p01v1AntiphaseTrapEnable, aad3014p01v1OverloadR, aad3014p01v1OverloadRTrapEnable, aad3014p01v1OverloadL, 
				aad3014p01v1OverloadLTrapEnable, aad3014p01v1OverloadRl, aad3014p01v1OverloadRlTrapEnable, aad3014p01v1LevelR, aad3014p01v1LevelL }
			STATUS current
			DESCRIPTION
				"Module AAD3014P01V1 Group"
			::= { varGroups 147901 }

		-- 1.3.6.1.4.1.10106.2.3.1.147902
		aad3014c01v2ModuleGroup OBJECT-GROUP
			OBJECTS {aad3014c01v2Index, aad3014c01v2Mono, aad3014c01v2GainR, aad3014c01v2GainL, aad3014c01v2OvlThrLevel, 
				aad3014c01v2SilThrLevel, aad3014c01v2NoSigTout, aad3014c01v2SilenceR, aad3014c01v2SilenceRTrapEnable, aad3014c01v2SilenceL, 
				aad3014c01v2SilenceLTrapEnable, aad3014c01v2OverloadR, aad3014c01v2OverloadRTrapEnable, aad3014c01v2OverloadL, aad3014c01v2OverloadLTrapEnable, 
				aad3014c01v2PkLevelR, aad3014c01v2PkLevelL, aad3014c01v2SerialNo }
			STATUS current
			DESCRIPTION
				"Module AAD3014C01V2 Group"
			::= { varGroups 147902 }

		-- 1.3.6.1.4.1.10106.2.3.1.148001
		aap0621p01v1ModuleGroup OBJECT-GROUP
			OBJECTS {aap0621p01v1Index, aap0621p01v1Output1, aap0621p01v1SwitchMode }
			STATUS current
			DESCRIPTION
				"Module AAP0621P01V1 Group"
			::= { varGroups 148001 }

		-- 1.3.6.1.4.1.10106.2.3.1.148101
		aap1222p01v1ModuleGroup OBJECT-GROUP
			OBJECTS {aap1222p01v1Index, aap1222p01v1Output1, aap1222p01v1Output2, aap1222p01v1SwitchMode }
			STATUS current
			DESCRIPTION
				"Module AAP1222P01V1 Group"
			::= { varGroups 148101 }

		-- 1.3.6.1.4.1.10106.2.3.1.149301
		sct3000c02v1ModuleGroup OBJECT-GROUP
			OBJECTS {sct3000c02v1Index, sct3000c02v1Mode, sct3000c02v1ModeTrapEnable, sct3000c02v1Input, sct3000c02v1InputTrapEnable, 
				sct3000c02v1Selin0, sct3000c02v1Selin1, sct3000c02v1SerialNo }
			STATUS current
			DESCRIPTION
				"Module SCT3000C02V1 Group"
			::= { varGroups 149301 }

		-- 1.3.6.1.4.1.10106.2.3.1.150501
		dat3000p01v1ModuleGroup OBJECT-GROUP
			OBJECTS {dat3000p01v1Index, dat3000p01v1InBits, dat3000p01v1OutBits, dat3000p01v1Mode, dat3000p01v1InputRef, 
				dat3000p01v1OutputFreq, dat3000p01v1MonoAes1, dat3000p01v1MuteAes1, dat3000p01v1MonoAes2, dat3000p01v1MuteAes2, 
				dat3000p01v1DelayPol, dat3000p01v1SyncMode, dat3000p01v1In192k, dat3000p01v1Out192k, dat3000p01v1FixDelay1, 
				dat3000p01v1FixDelay2, dat3000p01v1GainAes1A, dat3000p01v1PhaseAes1A, dat3000p01v1GainAes1B, dat3000p01v1PhaseAes1B, 
				dat3000p01v1GainAes2A, dat3000p01v1PhaseAes2A, dat3000p01v1GainAes2B, dat3000p01v1PhaseAes2B, dat3000p01v1Aes1AInput, 
				dat3000p01v1Aes1BInput, dat3000p01v1Aes2AInput, dat3000p01v1Aes2BInput, dat3000p01v1OutFreq, dat3000p01v1LockAes, 
				dat3000p01v1LockAesTrapEnable, dat3000p01v1LockVid, dat3000p01v1LockVidTrapEnable, dat3000p01v1LockWclk, dat3000p01v1LockWclkTrapEnable, 
				dat3000p01v1Aes2DetFreq, dat3000p01v1Aes1DetFreq, dat3000p01v1VarDelay1, dat3000p01v1VarDelay2, dat3000p01v1PeakLevOut1A, 
				dat3000p01v1PeakLevOut1B, dat3000p01v1PeakLevOut2A, dat3000p01v1PeakLevOut2B }
			STATUS current
			DESCRIPTION
				"Module DAT3000P01V1 Group"
			::= { varGroups 150501 }

		-- 1.3.6.1.4.1.10106.2.3.1.157401
		cav3000p01v1ModuleGroup OBJECT-GROUP
			OBJECTS {cav3000p01v1Index, cav3000p01v1AdLines, cav3000p01v1AdVbiMode, cav3000p01v1SyncSrc, cav3000p01v1NoAnalog, 
				cav3000p01v1NoAnalogTrapEnable, cav3000p01v1AnalogUnlock, cav3000p01v1AnalogUnlockTrapEnable, cav3000p01v1AnalogOvld, cav3000p01v1AnalogOvldTrapEnable, 
				cav3000p01v1AdFmt }
			STATUS current
			DESCRIPTION
				"Module CAV3000P01V1 Group"
			::= { varGroups 157401 }

		-- 1.3.6.1.4.1.10106.2.3.1.157501
		cav3001p01v1ModuleGroup OBJECT-GROUP
			OBJECTS {cav3001p01v1Index, cav3001p01v1DaLines, cav3001p01v1DaVbiMode, cav3001p01v1NoSdi, cav3001p01v1NoSdiTrapEnable, 
				cav3001p01v1SdiUnlock, cav3001p01v1SdiUnlockTrapEnable, cav3001p01v1DaFmt, cav3001p01v1EdhFullErr, cav3001p01v1EdhFullErrTrapEnable, 
				cav3001p01v1EdhActErr, cav3001p01v1EdhActErrTrapEnable }
			STATUS current
			DESCRIPTION
				"Module CAV3001P01V1 Group"
			::= { varGroups 157501 }

		-- 1.3.6.1.4.1.10106.2.3.1.157601
		cav3002p01v1ModuleGroup OBJECT-GROUP
			OBJECTS {cav3002p01v1Index, cav3002p01v1AdLines, cav3002p01v1AdVbiMode, cav3002p01v1SyncSrc, cav3002p01v1DaLines, 
				cav3002p01v1DaVbiMode, cav3002p01v1NoAnalog, cav3002p01v1NoAnalogTrapEnable, cav3002p01v1AnalogUnlock, cav3002p01v1AnalogUnlockTrapEnable, 
				cav3002p01v1AnalogOvld, cav3002p01v1AnalogOvldTrapEnable, cav3002p01v1AdFmt, cav3002p01v1NoSdi, cav3002p01v1NoSdiTrapEnable, 
				cav3002p01v1SdiUnlock, cav3002p01v1SdiUnlockTrapEnable, cav3002p01v1DaFmt, cav3002p01v1EdhFullErr, cav3002p01v1EdhFullErrTrapEnable, 
				cav3002p01v1EdhActErr, cav3002p01v1EdhActErrTrapEnable }
			STATUS current
			DESCRIPTION
				"Module CAV3002P01V1 Group"
			::= { varGroups 157601 }

		-- 1.3.6.1.4.1.10106.2.3.1.162801
		dsw3000c03v1ModuleGroup OBJECT-GROUP
			OBJECTS {dsw3000c03v1Index, dsw3000c03v1Mode, dsw3000c03v1ModeTrapEnable, dsw3000c03v1Buzzer, dsw3000c03v1Input, 
				dsw3000c03v1InputTrapEnable, dsw3000c03v1MainFail, dsw3000c03v1MainFailTrapEnable, dsw3000c03v1ExtMainFail, dsw3000c03v1ExtMainFailTrapEnable, 
				dsw3000c03v1ResFail, dsw3000c03v1ResFailTrapEnable, dsw3000c03v1ExtResFail, dsw3000c03v1ExtResFailTrapEnable, dsw3000c03v1AuxFail, 
				dsw3000c03v1AuxFailTrapEnable, dsw3000c03v1ExtAuxFail, dsw3000c03v1ExtAuxFailTrapEnable }
			STATUS current
			DESCRIPTION
				"Module DSW3000C03V1 Group"
			::= { varGroups 162801 }

		-- 1.3.6.1.4.1.10106.2.3.1.163501
		eap3000p01v1ModuleGroup OBJECT-GROUP
			OBJECTS {eap3000p01v1Index, eap3000p01v1ActivePreset, eap3000p01v1LoadPreset, eap3000p01v1SavePreset, eap3000p01v1GainCh1, 
				eap3000p01v1PhaseCh1, eap3000p01v1GainCh2, eap3000p01v1PhaseCh2, eap3000p01v1GainCh3, eap3000p01v1PhaseCh3, 
				eap3000p01v1GainCh4, eap3000p01v1PhaseCh4, eap3000p01v1Ch1Input, eap3000p01v1Ch2Input, eap3000p01v1Ch3Input, 
				eap3000p01v1Ch4Input, eap3000p01v1StCh1Input, eap3000p01v1StCh2Input, eap3000p01v1StCh3Input, eap3000p01v1StCh4Input, 
				eap3000p01v1MuteCh1, eap3000p01v1MuteCh2, eap3000p01v1MuteCh3, eap3000p01v1MuteCh4, eap3000p01v1AddCh1Ch2, 
				eap3000p01v1AddCh3Ch4, eap3000p01v1GroupProcess, eap3000p01v1HideVu, eap3000p01v1HideStat, eap3000p01v1ShowControl, 
				eap3000p01v1PeakHold, eap3000p01v1Process, eap3000p01v1SelMeasure, eap3000p01v1GroupMeasure, eap3000p01v1OverloadLevel, 
				eap3000p01v1SilenceLevel, eap3000p01v1SilenceTime, eap3000p01v1NoSig, eap3000p01v1NoSigTrapEnable, eap3000p01v1MaxEq, 
				eap3000p01v1EdhErr, eap3000p01v1PckAGr1, eap3000p01v1PckAGr2, eap3000p01v1PckAGr3, eap3000p01v1PckAGr4, 
				eap3000p01v1VuLevCh1, eap3000p01v1VuLevCh2, eap3000p01v1VuLevCh3, eap3000p01v1VuLevCh4, eap3000p01v1PeakLevCh1, 
				eap3000p01v1PeakLevCh2, eap3000p01v1PeakLevCh3, eap3000p01v1PeakLevCh4, eap3000p01v1Antiph12, eap3000p01v1Antiph12TrapEnable, 
				eap3000p01v1Antiph34, eap3000p01v1Antiph34TrapEnable, eap3000p01v1SilCh1, eap3000p01v1SilCh1TrapEnable, eap3000p01v1SilCh2, 
				eap3000p01v1SilCh2TrapEnable, eap3000p01v1SilCh3, eap3000p01v1SilCh3TrapEnable, eap3000p01v1SilCh4, eap3000p01v1SilCh4TrapEnable, 
				eap3000p01v1OvlCh1, eap3000p01v1OvlCh1TrapEnable, eap3000p01v1OvlCh2, eap3000p01v1OvlCh2TrapEnable, eap3000p01v1OvlCh3, 
				eap3000p01v1OvlCh3TrapEnable, eap3000p01v1OvlCh4, eap3000p01v1OvlCh4TrapEnable }
			STATUS current
			DESCRIPTION
				"Module EAP3000P01V1 Group"
			::= { varGroups 163501 }

		-- 1.3.6.1.4.1.10106.2.3.1.166801
		txe3000p01v1ModuleGroup OBJECT-GROUP
			OBJECTS {txe3000p01v1Index, txe3000p01v1TxBit1, txe3000p01v1TxBit2, txe3000p01v1TxBit3, txe3000p01v1TxtInsLine, 
				txe3000p01v1TxtIns, txe3000p01v1VitcRdLine, txe3000p01v1VitcRd, txe3000p01v1NoSignal, txe3000p01v1NoSignalTrapEnable, 
				txe3000p01v1EdhChk, txe3000p01v1VitcOk, txe3000p01v1Gpi1, txe3000p01v1Gpi2, txe3000p01v1Gpi3, 
				txe3000p01v1Gpi4, txe3000p01v1Bit1, txe3000p01v1Bit2, txe3000p01v1Bit3, txe3000p01v1Bit4, 
				txe3000p01v1VitcHour, txe3000p01v1VitcMin, txe3000p01v1VitcSec, txe3000p01v1VitcFrame }
			STATUS current
			DESCRIPTION
				"Module TXE3000P01V1 Group"
			::= { varGroups 166801 }

		-- 1.3.6.1.4.1.10106.2.3.1.166802
		txe3000p01v2ModuleGroup OBJECT-GROUP
			OBJECTS {txe3000p01v2Index, txe3000p01v2TxBit1, txe3000p01v2TxBit2, txe3000p01v2TxBit3, txe3000p01v2TxBit4, 
				txe3000p01v2TxtInsLine, txe3000p01v2TxtIns, txe3000p01v2VitcRdLine, txe3000p01v2VitcRd, txe3000p01v2NoSignal, 
				txe3000p01v2NoSignalTrapEnable, txe3000p01v2EdhChk, txe3000p01v2VitcOk, txe3000p01v2Gpi1, txe3000p01v2Gpi2, 
				txe3000p01v2Gpi3, txe3000p01v2Gpi4, txe3000p01v2Bit1, txe3000p01v2Bit2, txe3000p01v2Bit3, 
				txe3000p01v2Bit4, txe3000p01v2VitcHour, txe3000p01v2VitcMin, txe3000p01v2VitcSec, txe3000p01v2VitcFrame }
			STATUS current
			DESCRIPTION
				"Module TXE3000P01V2 Group"
			::= { varGroups 166802 }

		-- 1.3.6.1.4.1.10106.2.3.1.166901
		txd3000p01v1ModuleGroup OBJECT-GROUP
			OBJECTS {txd3000p01v1Index, txd3000p01v1GpoBit1, txd3000p01v1GpoBit2, txd3000p01v1GpoBit3, txd3000p01v1GpoBit4, 
				txd3000p01v1TxtRdLine, txd3000p01v1TxtClr, txd3000p01v1TxtRd, txd3000p01v1VitcInsLine, txd3000p01v1VitcIns, 
				txd3000p01v1NoSignal, txd3000p01v1NoSignalTrapEnable, txd3000p01v1TxtOk, txd3000p01v1Gpi1, txd3000p01v1Gpi2, 
				txd3000p01v1Gpi3, txd3000p01v1Gpi4, txd3000p01v1Bit1, txd3000p01v1Bit2, txd3000p01v1Bit3, 
				txd3000p01v1Bit4, txd3000p01v1VitcHour, txd3000p01v1VitcMin, txd3000p01v1VitcSec, txd3000p01v1VitcFrame }
			STATUS current
			DESCRIPTION
				"Module TXD3000P01V1 Group"
			::= { varGroups 166901 }

		-- 1.3.6.1.4.1.10106.2.3.1.166902
		txd3000p01v2ModuleGroup OBJECT-GROUP
			OBJECTS {txd3000p01v2Index, txd3000p01v2TxtRdLine, txd3000p01v2TxtClr, txd3000p01v2TxtRd, txd3000p01v2VitcInsLine, 
				txd3000p01v2VitcIns, txd3000p01v2GpoBit1, txd3000p01v2GpoBit2, txd3000p01v2GpoBit3, txd3000p01v2GpoBit4, 
				txd3000p01v2NoSignal, txd3000p01v2NoSignalTrapEnable, txd3000p01v2TxtOk, txd3000p01v2Gpi1, txd3000p01v2Gpi2, 
				txd3000p01v2Gpi3, txd3000p01v2Gpi4, txd3000p01v2Bit1, txd3000p01v2Bit2, txd3000p01v2Bit3, 
				txd3000p01v2Bit4, txd3000p01v2VitcHour, txd3000p01v2VitcMin, txd3000p01v2VitcSec, txd3000p01v2VitcFrame }
			STATUS current
			DESCRIPTION
				"Module TXD3000P01V2 Group"
			::= { varGroups 166902 }

		-- 1.3.6.1.4.1.10106.2.3.1.167201
		vfd3000c01v1ModuleGroup OBJECT-GROUP
			OBJECTS {vfd3000c01v1Index, vfd3000c01v1MainOutInput, vfd3000c01v1MainOutInputTrapEnable, vfd3000c01v1OutInput, vfd3000c01v1OutInputTrapEnable, 
				vfd3000c01v1ControlMode, vfd3000c01v1HideOsd, vfd3000c01v1FixedOsd, vfd3000c01v1Gpo0MskMaxEq, vfd3000c01v1Gpo0MskBadFmt, 
				vfd3000c01v1Gpo0MskEdhErr, vfd3000c01v1Gpo0MskFreeze, vfd3000c01v1Gpo0MskBlack, vfd3000c01v1Gpo1MskMaxEq, vfd3000c01v1Gpo1MskBadFmt, 
				vfd3000c01v1Gpo1MskEdhErr, vfd3000c01v1Gpo1MskFreeze, vfd3000c01v1Gpo1MskBlack, vfd3000c01v1Gpo2MskImageD, vfd3000c01v1Gpo2MskLevelD, 
				vfd3000c01v1Gpo3MskMaxEq, vfd3000c01v1Gpo3MskBadFmt, vfd3000c01v1Gpo3MskEdhErr, vfd3000c01v1Gpo3MskFreeze, vfd3000c01v1Gpo3MskBlack, 
				vfd3000c01v1BlackLevel, vfd3000c01v1ImageDispThres, vfd3000c01v1PeakDispThres, vfd3000c01v1BlckFrzTimeout, vfd3000c01v1MaxEqMMask, 
				vfd3000c01v1BadFmtMMask, vfd3000c01v1EdhErrMMask, vfd3000c01v1FreezeMMask, vfd3000c01v1BlackMMask, vfd3000c01v1MaxEqRMask, 
				vfd3000c01v1BadFmtRMask, vfd3000c01v1EdhErrRMask, vfd3000c01v1FreezeRMask, vfd3000c01v1BlackRMask, vfd3000c01v1ImageDispMask, 
				vfd3000c01v1LevelDispMask, vfd3000c01v1MaxEqM, vfd3000c01v1MaxEqMTrapEnable, vfd3000c01v1BadFmtM, vfd3000c01v1BadFmtMTrapEnable, 
				vfd3000c01v1EdhErrM, vfd3000c01v1EdhErrMTrapEnable, vfd3000c01v1BlackM, vfd3000c01v1BlackMTrapEnable, vfd3000c01v1FreezeM, 
				vfd3000c01v1FreezeMTrapEnable, vfd3000c01v1MaxEqR, vfd3000c01v1MaxEqRTrapEnable, vfd3000c01v1BadFmtR, vfd3000c01v1BadFmtRTrapEnable, 
				vfd3000c01v1EdhErrR, vfd3000c01v1EdhErrRTrapEnable, vfd3000c01v1BlackR, vfd3000c01v1BlackRTrapEnable, vfd3000c01v1FreezeR, 
				vfd3000c01v1FreezeRTrapEnable, vfd3000c01v1ImageDisp, vfd3000c01v1PeakDisp }
			STATUS current
			DESCRIPTION
				"Module VFD3000C01V1 Group"
			::= { varGroups 167201 }

		-- 1.3.6.1.4.1.10106.2.3.1.167501
		dar3000p01v1ModuleGroup OBJECT-GROUP
			OBJECTS {dar3000p01v1Index, dar3000p01v1Bits, dar3000p01v10dbLevel, dar3000p01v1Mode, dar3000p01v1InputRef, 
				dar3000p01v1OutputFreq, dar3000p01v1DipEnable, dar3000p01v1OptLevel, dar3000p01v1AudFreqCh1L, dar3000p01v1AudFreqCh1R, 
				dar3000p01v1AudFreqCh2L, dar3000p01v1AudFreqCh2R, dar3000p01v1OutFreq, dar3000p01v1UnlockAes, dar3000p01v1UnlockAesTrapEnable, 
				dar3000p01v1UnlockVid, dar3000p01v1UnlockVidTrapEnable, dar3000p01v1UnlockWclk, dar3000p01v1UnlockWclkTrapEnable, dar3000p01v1NoAes, 
				dar3000p01v1NoAesTrapEnable, dar3000p01v1NoVid, dar3000p01v1NoVidTrapEnable, dar3000p01v1NoWclk, dar3000p01v1NoWclkTrapEnable, 
				dar3000p01v1SilenceL, dar3000p01v1SilenceR, dar3000p01v1SilenceCh1, dar3000p01v1SilenceCh2 }
			STATUS current
			DESCRIPTION
				"Module DAR3000P01V1 Group"
			::= { varGroups 167501 }

		-- 1.3.6.1.4.1.10106.2.3.1.184801
		txt3000p01v1ModuleGroup OBJECT-GROUP
			OBJECTS {txt3000p01v1Index, txt3000p01v1InsEna, txt3000p01v1Preset, txt3000p01v1NoSigPgm, txt3000p01v1NoSigPgmTrapEnable, 
				txt3000p01v1MaxEqPgm, txt3000p01v1EdhErrPgm, txt3000p01v1NoSigSrc, txt3000p01v1NoSigSrcTrapEnable, txt3000p01v1MaxEqSrc, 
				txt3000p01v1EdhErrSrc }
			STATUS current
			DESCRIPTION
				"Module TXT3000P01V1 Group"
			::= { varGroups 184801 }

		-- 1.3.6.1.4.1.10106.2.3.1.187601
		dvp3224p01v1ModuleGroup OBJECT-GROUP
			OBJECTS {dvp3224p01v1Index, dvp3224p01v1Output1, dvp3224p01v1Output2, dvp3224p01v1Output3, dvp3224p01v1Output4, 
				dvp3224p01v1SwitchTime, dvp3224p01v1NoSync, dvp3224p01v1SyncLines }
			STATUS current
			DESCRIPTION
				"Module DVP3224P01V1 Group"
			::= { varGroups 187601 }

		-- 1.3.6.1.4.1.10106.2.3.1.195701
		gps3000p01v1ModuleGroup OBJECT-GROUP
			OBJECTS {gps3000p01v1Index, gps3000p01v1Holdover, gps3000p01v1HoldoverTrapEnable, gps3000p01v1CableDelay, gps3000p01v1VideoOut, 
				gps3000p01v1SdiVidHDelay, gps3000p01v1SdiVidVDelay, gps3000p01v1SdiVidFrDelay, gps3000p01v1AnaVidHDelay, gps3000p01v1VitcInsLine, 
				gps3000p01v1AnaVidSch, gps3000p01v1HoldoverStat, gps3000p01v1HoldoverStatTrapEnable, gps3000p01v1RedundFail, gps3000p01v1RedundFailTrapEnable, 
				gps3000p01v1OutputsMuted, gps3000p01v1OutputsMutedTrapEnable, gps3000p01v1SatRxStat, gps3000p01v1AntenaStat, gps3000p01v1AntenaStatTrapEnable, 
				gps3000p01v1SatNoFail, gps3000p01v1AlmanacFail, gps3000p01v1GpsModFail, gps3000p01v1GpsTrackSats, gps3000p01v1GpsVisibleSats, 
				gps3000p01v1GpsSignalLevel, gps3000p01v1AdquisitionStat, gps3000p01v1HoldoverTime, gps3000p01v1FreqDriftEst, gps3000p01v1PhaseDriftEst }
			STATUS current
			DESCRIPTION
				"Module GPS3000P01V1 Group"
			::= { varGroups 195701 }

		-- 1.3.6.1.4.1.10106.2.3.1.195702
		gps3000p01v2ModuleGroup OBJECT-GROUP
			OBJECTS {gps3000p01v2Index, gps3000p01v2Holdover, gps3000p01v2HoldoverTrapEnable, gps3000p01v2CableDelay, gps3000p01v2VideoOut, 
				gps3000p01v2SdiVidHDelay, gps3000p01v2SdiVidVDelay, gps3000p01v2SdiVidFrDelay, gps3000p01v2AnaVidHDelay, gps3000p01v2VitcInsLine, 
				gps3000p01v2AnaVidSch, gps3000p01v2HoldoverStat, gps3000p01v2HoldoverStatTrapEnable, gps3000p01v2RedundFail, gps3000p01v2RedundFailTrapEnable, 
				gps3000p01v2OutputsMuted, gps3000p01v2OutputsMutedTrapEnable, gps3000p01v2SatRxStat, gps3000p01v2AntenaStat, gps3000p01v2AntenaStatTrapEnable, 
				gps3000p01v2SatNoFail, gps3000p01v2AlmanacFail, gps3000p01v2GpsModFail, gps3000p01v2GpsTrackSats, gps3000p01v2GpsVisibleSats, 
				gps3000p01v2GpsSignalLevel, gps3000p01v2AdquisitionStat, gps3000p01v2HoldoverTime, gps3000p01v2FreqDriftEst, gps3000p01v2PhaseDriftEst }
			STATUS current
			DESCRIPTION
				"Module GPS3000P01V2 Group"
			::= { varGroups 195702 }

		-- 1.3.6.1.4.1.10106.2.3.1.195703
		gps3000p01v3ModuleGroup OBJECT-GROUP
			OBJECTS {gps3000p01v3Index, gps3000p01v3Holdover, gps3000p01v3HoldoverTrapEnable, gps3000p01v3CableDelay, gps3000p01v3VideoOut, 
				gps3000p01v3SdiVidHDelay, gps3000p01v3SdiVidVDelay, gps3000p01v3SdiVidFrDelay, gps3000p01v3AnaVidHDelay, gps3000p01v3VitcInsLine, 
				gps3000p01v3AnaVidSch, gps3000p01v3HoldoverStat, gps3000p01v3HoldoverStatTrapEnable, gps3000p01v3RedundFail, gps3000p01v3RedundFailTrapEnable, 
				gps3000p01v3OutputsMuted, gps3000p01v3OutputsMutedTrapEnable, gps3000p01v3SatRxStat, gps3000p01v3AntenaStat, gps3000p01v3AntenaStatTrapEnable, 
				gps3000p01v3SatNoFail, gps3000p01v3AlmanacFail, gps3000p01v3GpsModFail, gps3000p01v3GpsTrackSats, gps3000p01v3GpsVisibleSats, 
				gps3000p01v3GpsSignalLevel, gps3000p01v3AdquisitionStat, gps3000p01v3HoldoverTime, gps3000p01v3FreqDriftEst, gps3000p01v3PhaseDriftEst }
			STATUS current
			DESCRIPTION
				"Module GPS3000P01V3 Group"
			::= { varGroups 195703 }

		-- 1.3.6.1.4.1.10106.2.3.1.195704
		gps3000p01v4ModuleGroup OBJECT-GROUP
			OBJECTS {gps3000p01v4Index, gps3000p01v4Holdover, gps3000p01v4HoldoverTrapEnable, gps3000p01v4CableDelay, gps3000p01v4VideoOut, 
				gps3000p01v4SdiVidHDelay, gps3000p01v4SdiVidVDelay, gps3000p01v4SdiVidFrDelay, gps3000p01v4AnaVidHDelay, gps3000p01v4VitcInsLine, 
				gps3000p01v4AnaVidSch, gps3000p01v4HoldoverStat, gps3000p01v4HoldoverStatTrapEnable, gps3000p01v4RedundFail, gps3000p01v4RedundFailTrapEnable, 
				gps3000p01v4OutputsMuted, gps3000p01v4OutputsMutedTrapEnable, gps3000p01v4SatRxStat, gps3000p01v4AntenaStat, gps3000p01v4AntenaStatTrapEnable, 
				gps3000p01v4SatNoFail, gps3000p01v4AlmanacFail, gps3000p01v4GpsModFail, gps3000p01v4GpsTrackSats, gps3000p01v4GpsVisibleSats, 
				gps3000p01v4GpsSignalLevel, gps3000p01v4AdquisitionStat, gps3000p01v4HoldoverTime, gps3000p01v4FreqDriftEst, gps3000p01v4PhaseDriftEst }
			STATUS current
			DESCRIPTION
				"Module GPS3000P01V4 Group"
			::= { varGroups 195704 }

		-- 1.3.6.1.4.1.10106.2.3.1.207201
		sdt3000p01v1ModuleGroup OBJECT-GROUP
			OBJECTS {sdt3000p01v1Index, sdt3000p01v1NoSigA, sdt3000p01v1NoSigATrapEnable, sdt3000p01v1LaserFailA, sdt3000p01v1LaserFailATrapEnable, 
				sdt3000p01v1NoSigB, sdt3000p01v1NoSigBTrapEnable, sdt3000p01v1LaserFailB, sdt3000p01v1LaserFailBTrapEnable }
			STATUS current
			DESCRIPTION
				"Module SDT3000P01V1 Group"
			::= { varGroups 207201 }

		-- 1.3.6.1.4.1.10106.2.3.1.207301
		sdr3000p01v1ModuleGroup OBJECT-GROUP
			OBJECTS {sdr3000p01v1Index, sdr3000p01v1NoSigA, sdr3000p01v1NoSigATrapEnable, sdr3000p01v1NoSigB, sdr3000p01v1NoSigBTrapEnable, 
				sdr3000p01v1RxPowerA, sdr3000p01v1RxPowerB }
			STATUS current
			DESCRIPTION
				"Module SDR3000P01V1 Group"
			::= { varGroups 207301 }

		-- 1.3.6.1.4.1.10106.2.3.1.211201
		dsw3000p05v1ModuleGroup OBJECT-GROUP
			OBJECTS {dsw3000p05v1Index, dsw3000p05v1Mode, dsw3000p05v1ModeTrapEnable, dsw3000p05v1Buzzer, dsw3000p05v1Input, 
				dsw3000p05v1InputTrapEnable, dsw3000p05v1MainFail, dsw3000p05v1MainFailTrapEnable, dsw3000p05v1ExtMainFail, dsw3000p05v1ExtMainFailTrapEnable, 
				dsw3000p05v1ResFail, dsw3000p05v1ResFailTrapEnable, dsw3000p05v1ExtResFail, dsw3000p05v1ExtResFailTrapEnable, dsw3000p05v1AuxFail, 
				dsw3000p05v1AuxFailTrapEnable, dsw3000p05v1ExtAuxFail, dsw3000p05v1ExtAuxFailTrapEnable }
			STATUS current
			DESCRIPTION
				"Module DSW3000P05V1 Group"
			::= { varGroups 211201 }

		-- 1.3.6.1.4.1.10106.2.3.1.213201
		gps3000p02v1ModuleGroup OBJECT-GROUP
			OBJECTS {gps3000p02v1Index, gps3000p02v1Holdover, gps3000p02v1HoldoverTrapEnable, gps3000p02v1CableDelay, gps3000p02v1VideoOut, 
				gps3000p02v1SdiVidHDelay, gps3000p02v1SdiVidVDelay, gps3000p02v1SdiVidFrDelay, gps3000p02v1AnaVidHDelay, gps3000p02v1VitcInsLine, 
				gps3000p02v1AnaVidSch, gps3000p02v1HoldoverStat, gps3000p02v1HoldoverStatTrapEnable, gps3000p02v1RedundFail, gps3000p02v1RedundFailTrapEnable, 
				gps3000p02v1OutputsMuted, gps3000p02v1OutputsMutedTrapEnable, gps3000p02v1SatRxStat, gps3000p02v1AntenaStat, gps3000p02v1AntenaStatTrapEnable, 
				gps3000p02v1SatNoFail, gps3000p02v1AlmanacFail, gps3000p02v1GpsModFail, gps3000p02v1GpsTrackSats, gps3000p02v1GpsVisibleSats, 
				gps3000p02v1GpsSignalLevel, gps3000p02v1AdquisitionStat, gps3000p02v1HoldoverTime, gps3000p02v1FreqDriftEst, gps3000p02v1PhaseDriftEst }
			STATUS current
			DESCRIPTION
				"Module GPS3000P02V1 Group"
			::= { varGroups 213201 }

		-- 1.3.6.1.4.1.10106.2.3.1.213202
		gps3000p02v2ModuleGroup OBJECT-GROUP
			OBJECTS {gps3000p02v2Index, gps3000p02v2Holdover, gps3000p02v2HoldoverTrapEnable, gps3000p02v2CableDelay, gps3000p02v2VideoOut, 
				gps3000p02v2SdiVidHDelay, gps3000p02v2SdiVidVDelay, gps3000p02v2SdiVidFrDelay, gps3000p02v2AnaVidHDelay, gps3000p02v2VitcInsLine, 
				gps3000p02v2AnaVidSch, gps3000p02v2HoldoverStat, gps3000p02v2HoldoverStatTrapEnable, gps3000p02v2RedundFail, gps3000p02v2RedundFailTrapEnable, 
				gps3000p02v2OutputsMuted, gps3000p02v2OutputsMutedTrapEnable, gps3000p02v2SatRxStat, gps3000p02v2AntenaStat, gps3000p02v2AntenaStatTrapEnable, 
				gps3000p02v2SatNoFail, gps3000p02v2AlmanacFail, gps3000p02v2GpsModFail, gps3000p02v2GpsTrackSats, gps3000p02v2GpsVisibleSats, 
				gps3000p02v2GpsSignalLevel, gps3000p02v2AdquisitionStat, gps3000p02v2HoldoverTime, gps3000p02v2FreqDriftEst, gps3000p02v2PhaseDriftEst }
			STATUS current
			DESCRIPTION
				"Module GPS3000P02V2 Group"
			::= { varGroups 213202 }

		-- 1.3.6.1.4.1.10106.2.3.1.213203
		gps3000p02v3ModuleGroup OBJECT-GROUP
			OBJECTS {gps3000p02v3Index, gps3000p02v3Holdover, gps3000p02v3HoldoverTrapEnable, gps3000p02v3CableDelay, gps3000p02v3VideoOut, 
				gps3000p02v3SdiVidHDelay, gps3000p02v3SdiVidVDelay, gps3000p02v3SdiVidFrDelay, gps3000p02v3AnaVidHDelay, gps3000p02v3VitcInsLine, 
				gps3000p02v3AnaVidSch, gps3000p02v3HoldoverStat, gps3000p02v3HoldoverStatTrapEnable, gps3000p02v3RedundFail, gps3000p02v3RedundFailTrapEnable, 
				gps3000p02v3OutputsMuted, gps3000p02v3OutputsMutedTrapEnable, gps3000p02v3SatRxStat, gps3000p02v3AntenaStat, gps3000p02v3AntenaStatTrapEnable, 
				gps3000p02v3SatNoFail, gps3000p02v3AlmanacFail, gps3000p02v3GpsModFail, gps3000p02v3GpsTrackSats, gps3000p02v3GpsVisibleSats, 
				gps3000p02v3GpsSignalLevel, gps3000p02v3AdquisitionStat, gps3000p02v3HoldoverTime, gps3000p02v3FreqDriftEst, gps3000p02v3PhaseDriftEst }
			STATUS current
			DESCRIPTION
				"Module GPS3000P02V3 Group"
			::= { varGroups 213203 }

		-- 1.3.6.1.4.1.10106.2.3.1.213204
		gps3000p02v4ModuleGroup OBJECT-GROUP
			OBJECTS {gps3000p02v4Index, gps3000p02v4Holdover, gps3000p02v4HoldoverTrapEnable, gps3000p02v4CableDelay, gps3000p02v4VideoOut, 
				gps3000p02v4SdiVidHDelay, gps3000p02v4SdiVidVDelay, gps3000p02v4SdiVidFrDelay, gps3000p02v4AnaVidHDelay, gps3000p02v4VitcInsLine, 
				gps3000p02v4AnaVidSch, gps3000p02v4HoldoverStat, gps3000p02v4HoldoverStatTrapEnable, gps3000p02v4RedundFail, gps3000p02v4RedundFailTrapEnable, 
				gps3000p02v4OutputsMuted, gps3000p02v4OutputsMutedTrapEnable, gps3000p02v4SatRxStat, gps3000p02v4AntenaStat, gps3000p02v4AntenaStatTrapEnable, 
				gps3000p02v4SatNoFail, gps3000p02v4AlmanacFail, gps3000p02v4GpsModFail, gps3000p02v4GpsTrackSats, gps3000p02v4GpsVisibleSats, 
				gps3000p02v4GpsSignalLevel, gps3000p02v4AdquisitionStat, gps3000p02v4HoldoverTime, gps3000p02v4FreqDriftEst, gps3000p02v4PhaseDriftEst }
			STATUS current
			DESCRIPTION
				"Module GPS3000P02V4 Group"
			::= { varGroups 213204 }

		-- 1.3.6.1.4.1.10106.2.3.1.215401
		pds3001p01v1ModuleGroup OBJECT-GROUP
			OBJECTS {pds3001p01v1Index, pds3001p01v1BlackLevel, pds3001p01v1MeanDispThres, pds3001p01v1PeakDispThres, pds3001p01v1BlckTimeout, 
				pds3001p01v1FreezeTimeout, pds3001p01v1UnlockMask, pds3001p01v1BlackMask, pds3001p01v1PeakFreezeMask, pds3001p01v1MeanFreezeMask, 
				pds3001p01v1Gpo1MskUnlock, pds3001p01v1Gpo1MskBlack, pds3001p01v1Gpo1MskFreeze, pds3001p01v1Gpo2MskUnlock, pds3001p01v1Gpo2MskBlack, 
				pds3001p01v1Gpo2MskFreeze, pds3001p01v1Unlock, pds3001p01v1UnlockTrapEnable, pds3001p01v1Black, pds3001p01v1BlackTrapEnable, 
				pds3001p01v1Freeze, pds3001p01v1FreezeTrapEnable, pds3001p01v1UnlockT, pds3001p01v1UnlockTTrapEnable, pds3001p01v1BlackT, 
				pds3001p01v1BlackTTrapEnable, pds3001p01v1FreezeT, pds3001p01v1FreezeTTrapEnable, pds3001p01v1Overload, pds3001p01v1OverloadTrapEnable }
			STATUS current
			DESCRIPTION
				"Module PDS3001P01V1 Group"
			::= { varGroups 215401 }

		-- 1.3.6.1.4.1.10106.2.3.1.216401
		gps3000p03v1ModuleGroup OBJECT-GROUP
			OBJECTS {gps3000p03v1Index, gps3000p03v1Holdover, gps3000p03v1HoldoverTrapEnable, gps3000p03v1CableDelay, gps3000p03v1VideoOut, 
				gps3000p03v1SdiVidHDelay, gps3000p03v1SdiVidVDelay, gps3000p03v1SdiVidFrDelay, gps3000p03v1AnaVidHDelay, gps3000p03v1VitcInsLine, 
				gps3000p03v1AnaVidSch, gps3000p03v1HoldoverStat, gps3000p03v1HoldoverStatTrapEnable, gps3000p03v1RedundFail, gps3000p03v1RedundFailTrapEnable, 
				gps3000p03v1OutputsMuted, gps3000p03v1OutputsMutedTrapEnable, gps3000p03v1SatRxStat, gps3000p03v1AntenaStat, gps3000p03v1AntenaStatTrapEnable, 
				gps3000p03v1SatNoFail, gps3000p03v1AlmanacFail, gps3000p03v1GpsModFail, gps3000p03v1GpsTrackSats, gps3000p03v1GpsVisibleSats, 
				gps3000p03v1GpsSignalLevel, gps3000p03v1AdquisitionStat, gps3000p03v1HoldoverTime, gps3000p03v1FreqDriftEst, gps3000p03v1PhaseDriftEst }
			STATUS current
			DESCRIPTION
				"Module GPS3000P03V1 Group"
			::= { varGroups 216401 }

		-- 1.3.6.1.4.1.10106.2.3.1.216402
		gps3000p03v2ModuleGroup OBJECT-GROUP
			OBJECTS {gps3000p03v2Index, gps3000p03v2Holdover, gps3000p03v2HoldoverTrapEnable, gps3000p03v2CableDelay, gps3000p03v2VideoOut, 
				gps3000p03v2SdiVidHDelay, gps3000p03v2SdiVidVDelay, gps3000p03v2SdiVidFrDelay, gps3000p03v2AnaVidHDelay, gps3000p03v2VitcInsLine, 
				gps3000p03v2AnaVidSch, gps3000p03v2HoldoverStat, gps3000p03v2HoldoverStatTrapEnable, gps3000p03v2RedundFail, gps3000p03v2RedundFailTrapEnable, 
				gps3000p03v2OutputsMuted, gps3000p03v2OutputsMutedTrapEnable, gps3000p03v2SatRxStat, gps3000p03v2AntenaStat, gps3000p03v2AntenaStatTrapEnable, 
				gps3000p03v2SatNoFail, gps3000p03v2AlmanacFail, gps3000p03v2GpsModFail, gps3000p03v2GpsTrackSats, gps3000p03v2GpsVisibleSats, 
				gps3000p03v2GpsSignalLevel, gps3000p03v2AdquisitionStat, gps3000p03v2HoldoverTime, gps3000p03v2FreqDriftEst, gps3000p03v2PhaseDriftEst }
			STATUS current
			DESCRIPTION
				"Module GPS3000P03V2 Group"
			::= { varGroups 216402 }

		-- 1.3.6.1.4.1.10106.2.3.1.216403
		gps3000p03v3ModuleGroup OBJECT-GROUP
			OBJECTS {gps3000p03v3Index, gps3000p03v3Holdover, gps3000p03v3HoldoverTrapEnable, gps3000p03v3CableDelay, gps3000p03v3VideoOut, 
				gps3000p03v3SdiVidHDelay, gps3000p03v3SdiVidVDelay, gps3000p03v3SdiVidFrDelay, gps3000p03v3AnaVidHDelay, gps3000p03v3VitcInsLine, 
				gps3000p03v3AnaVidSch, gps3000p03v3HoldoverStat, gps3000p03v3HoldoverStatTrapEnable, gps3000p03v3RedundFail, gps3000p03v3RedundFailTrapEnable, 
				gps3000p03v3OutputsMuted, gps3000p03v3OutputsMutedTrapEnable, gps3000p03v3SatRxStat, gps3000p03v3AntenaStat, gps3000p03v3AntenaStatTrapEnable, 
				gps3000p03v3SatNoFail, gps3000p03v3AlmanacFail, gps3000p03v3GpsModFail, gps3000p03v3GpsTrackSats, gps3000p03v3GpsVisibleSats, 
				gps3000p03v3GpsSignalLevel, gps3000p03v3AdquisitionStat, gps3000p03v3HoldoverTime, gps3000p03v3FreqDriftEst, gps3000p03v3PhaseDriftEst }
			STATUS current
			DESCRIPTION
				"Module GPS3000P03V3 Group"
			::= { varGroups 216403 }

		-- 1.3.6.1.4.1.10106.2.3.1.216404
		gps3000p03v4ModuleGroup OBJECT-GROUP
			OBJECTS {gps3000p03v4Index, gps3000p03v4Holdover, gps3000p03v4HoldoverTrapEnable, gps3000p03v4CableDelay, gps3000p03v4VideoOut, 
				gps3000p03v4SdiVidHDelay, gps3000p03v4SdiVidVDelay, gps3000p03v4SdiVidFrDelay, gps3000p03v4AnaVidHDelay, gps3000p03v4VitcInsLine, 
				gps3000p03v4AnaVidSch, gps3000p03v4HoldoverStat, gps3000p03v4HoldoverStatTrapEnable, gps3000p03v4RedundFail, gps3000p03v4RedundFailTrapEnable, 
				gps3000p03v4OutputsMuted, gps3000p03v4OutputsMutedTrapEnable, gps3000p03v4SatRxStat, gps3000p03v4AntenaStat, gps3000p03v4AntenaStatTrapEnable, 
				gps3000p03v4SatNoFail, gps3000p03v4AlmanacFail, gps3000p03v4GpsModFail, gps3000p03v4GpsTrackSats, gps3000p03v4GpsVisibleSats, 
				gps3000p03v4GpsSignalLevel, gps3000p03v4AdquisitionStat, gps3000p03v4HoldoverTime, gps3000p03v4FreqDriftEst, gps3000p03v4PhaseDriftEst }
			STATUS current
			DESCRIPTION
				"Module GPS3000P03V4 Group"
			::= { varGroups 216404 }

		-- 1.3.6.1.4.1.10106.2.3.1.224701
		frs3004c02v1ModuleGroup OBJECT-GROUP
			OBJECTS {frs3004c02v1Index, frs3004c02v1RefSource, frs3004c02v1FailMode, frs3004c02v1SynchroMode, frs3004c02v1VbiMode, 
				frs3004c02v1HDelay1, frs3004c02v1VDelay1, frs3004c02v1LumaGain1, frs3004c02v1ChromaGain1, frs3004c02v1BlackOffset1, 
				frs3004c02v1HDelay2, frs3004c02v1VDelay2, frs3004c02v1LumaGain2, frs3004c02v1ChromaGain2, frs3004c02v1BlackOffset2, 
				frs3004c02v1HDelay3, frs3004c02v1VDelay3, frs3004c02v1LumaGain3, frs3004c02v1ChromaGain3, frs3004c02v1BlackOffset3, 
				frs3004c02v1HDelay4, frs3004c02v1VDelay4, frs3004c02v1LumaGain4, frs3004c02v1ChromaGain4, frs3004c02v1BlackOffset4, 
				frs3004c02v1NoRef, frs3004c02v1NoRefTrapEnable, frs3004c02v1RefUnlock, frs3004c02v1RefUnlockTrapEnable, frs3004c02v1RefEdhError, 
				frs3004c02v1RefLines, frs3004c02v1NoSig1, frs3004c02v1NoSig1TrapEnable, frs3004c02v1NoSig2, frs3004c02v1NoSig2TrapEnable, 
				frs3004c02v1NoSig3, frs3004c02v1NoSig3TrapEnable, frs3004c02v1NoSig4, frs3004c02v1NoSig4TrapEnable, frs3004c02v1EdhError1, 
				frs3004c02v1EdhError2, frs3004c02v1EdhError3, frs3004c02v1EdhError4, frs3004c02v1Sig1Delay, frs3004c02v1Sig2Delay, 
				frs3004c02v1Sig3Delay, frs3004c02v1Sig4Delay, frs3004c02v1SerialNo }
			STATUS current
			DESCRIPTION
				"Module FRS3004C02V1 Group"
			::= { varGroups 224701 }

		-- 1.3.6.1.4.1.10106.2.3.1.226401
		kbd3100p01v1ModuleGroup OBJECT-GROUP
			OBJECTS {kbd3100p01v1Index, kbd3100p01v1BeepEna, kbd3100p01v1ShowErr, kbd3100p01v1InvertGpi1Pol, kbd3100p01v1InvertGpi2Pol, 
				kbd3100p01v1InvertGpi3Pol, kbd3100p01v1InvertGpi4Pol, kbd3100p01v1InvertGpi5Pol, kbd3100p01v1InvertGpi6Pol, kbd3100p01v1InvertGpi7Pol, 
				kbd3100p01v1InvertGpi8Pol, kbd3100p01v1Gpi1, kbd3100p01v1Gpi2, kbd3100p01v1Gpi3, kbd3100p01v1Gpi4, 
				kbd3100p01v1Gpi5, kbd3100p01v1Gpi6, kbd3100p01v1Gpi7, kbd3100p01v1Gpi8 }
			STATUS current
			DESCRIPTION
				"Module KBD3100P01V1 Group"
			::= { varGroups 226401 }

		-- 1.3.6.1.4.1.10106.2.3.1.229601
		dvd3001p01v1ModuleGroup OBJECT-GROUP
			OBJECTS {dvd3001p01v1Index, dvd3001p01v1NoSigA, dvd3001p01v1NoSigATrapEnable, dvd3001p01v1MaxEqA, dvd3001p01v1NoSigB, 
				dvd3001p01v1NoSigBTrapEnable, dvd3001p01v1MaxEqB, dvd3001p01v1CableLengthA, dvd3001p01v1CableLengthB }
			STATUS current
			DESCRIPTION
				"Module DVD3001P01V1 Group"
			::= { varGroups 229601 }

		-- 1.3.6.1.4.1.10106.2.3.1.232401
		frs3004c01v1ModuleGroup OBJECT-GROUP
			OBJECTS {frs3004c01v1Index, frs3004c01v1RefSource, frs3004c01v1FailMode, frs3004c01v1SynchroMode, frs3004c01v1VbiMode, 
				frs3004c01v1HDelay1, frs3004c01v1VDelay1, frs3004c01v1LumaGain1, frs3004c01v1ChromaGain1, frs3004c01v1BlackOffset1, 
				frs3004c01v1HDelay2, frs3004c01v1VDelay2, frs3004c01v1LumaGain2, frs3004c01v1ChromaGain2, frs3004c01v1BlackOffset2, 
				frs3004c01v1HDelay3, frs3004c01v1VDelay3, frs3004c01v1LumaGain3, frs3004c01v1ChromaGain3, frs3004c01v1BlackOffset3, 
				frs3004c01v1HDelay4, frs3004c01v1VDelay4, frs3004c01v1LumaGain4, frs3004c01v1ChromaGain4, frs3004c01v1BlackOffset4, 
				frs3004c01v1NoRef, frs3004c01v1NoRefTrapEnable, frs3004c01v1RefUnlock, frs3004c01v1RefUnlockTrapEnable, frs3004c01v1RefEdhError, 
				frs3004c01v1RefLines, frs3004c01v1NoSig1, frs3004c01v1NoSig1TrapEnable, frs3004c01v1NoSig2, frs3004c01v1NoSig2TrapEnable, 
				frs3004c01v1NoSig3, frs3004c01v1NoSig3TrapEnable, frs3004c01v1NoSig4, frs3004c01v1NoSig4TrapEnable, frs3004c01v1EdhError1, 
				frs3004c01v1EdhError2, frs3004c01v1EdhError3, frs3004c01v1EdhError4, frs3004c01v1Sig1Delay, frs3004c01v1Sig2Delay, 
				frs3004c01v1Sig3Delay, frs3004c01v1Sig4Delay, frs3004c01v1SerialNo }
			STATUS current
			DESCRIPTION
				"Module FRS3004C01V1 Group"
			::= { varGroups 232401 }

		-- 1.3.6.1.4.1.10106.2.3.1.233401
		dvd3001c02v1ModuleGroup OBJECT-GROUP
			OBJECTS {dvd3001c02v1Index, dvd3001c02v1NoSigA, dvd3001c02v1NoSigATrapEnable, dvd3001c02v1MaxEqA, dvd3001c02v1NoSigB, 
				dvd3001c02v1NoSigBTrapEnable, dvd3001c02v1MaxEqB, dvd3001c02v1DvdMode, dvd3001c02v1CableLengthA, dvd3001c02v1CableLengthB, 
				dvd3001c02v1SerialNo }
			STATUS current
			DESCRIPTION
				"Module DVD3001C02V1 Group"
			::= { varGroups 233401 }

		-- 1.3.6.1.4.1.10106.2.3.1.233501
		dvd3001c03v1ModuleGroup OBJECT-GROUP
			OBJECTS {dvd3001c03v1Index, dvd3001c03v1NoSigA, dvd3001c03v1NoSigATrapEnable, dvd3001c03v1MaxEqA, dvd3001c03v1NoSigB, 
				dvd3001c03v1NoSigBTrapEnable, dvd3001c03v1MaxEqB, dvd3001c03v1DvdMode, dvd3001c03v1CableLengthA, dvd3001c03v1CableLengthB, 
				dvd3001c03v1SerialNo }
			STATUS current
			DESCRIPTION
				"Module DVD3001C03V1 Group"
			::= { varGroups 233501 }

		-- 1.3.6.1.4.1.10106.2.3.1.234101
		dvd3001c04v1ModuleGroup OBJECT-GROUP
			OBJECTS {dvd3001c04v1Index, dvd3001c04v1NoSigA, dvd3001c04v1NoSigATrapEnable, dvd3001c04v1MaxEqA, dvd3001c04v1CableLengthA, 
				dvd3001c04v1SerialNo }
			STATUS current
			DESCRIPTION
				"Module DVD3001C04V1 Group"
			::= { varGroups 234101 }

		-- 1.3.6.1.4.1.10106.2.3.1.234201
		dvd3001c05v1ModuleGroup OBJECT-GROUP
			OBJECTS {dvd3001c05v1Index, dvd3001c05v1NoSigA, dvd3001c05v1NoSigATrapEnable, dvd3001c05v1MaxEqA, dvd3001c05v1CableLengthA, 
				dvd3001c05v1SerialNo }
			STATUS current
			DESCRIPTION
				"Module DVD3001C05V1 Group"
			::= { varGroups 234201 }

		-- 1.3.6.1.4.1.10106.2.3.1.238701
		sdr3000p02v1ModuleGroup OBJECT-GROUP
			OBJECTS {sdr3000p02v1Index, sdr3000p02v1NoSigA, sdr3000p02v1NoSigATrapEnable, sdr3000p02v1NoSigB, sdr3000p02v1NoSigBTrapEnable, 
				sdr3000p02v1RxPowerA, sdr3000p02v1RxPowerB }
			STATUS current
			DESCRIPTION
				"Module SDR3000P02V1 Group"
			::= { varGroups 238701 }

		-- 1.3.6.1.4.1.10106.2.3.1.241501
		asw3000c01v1ModuleGroup OBJECT-GROUP
			OBJECTS {asw3000c01v1Index, asw3000c01v1Mode, asw3000c01v1ModeTrapEnable, asw3000c01v1Buzzer, asw3000c01v1Input, 
				asw3000c01v1InputTrapEnable, asw3000c01v1GpiMask, asw3000c01v1PresenceMask, asw3000c01v1SyncLMask, asw3000c01v1SyncBMask, 
				asw3000c01v1PatErrMask, asw3000c01v1PatCcMask, asw3000c01v1BitrateMask, asw3000c01v1NullPckMask, asw3000c01v1BitrateMin, 
				asw3000c01v1BitrateMax, asw3000c01v1PckNullMin, asw3000c01v1PckNullMax, asw3000c01v1ActTime, asw3000c01v1RecTime, 
				asw3000c01v1PatTimeout, asw3000c01v1InvertPriority, asw3000c01v1MainPckBytes, asw3000c01v1MainGlobalFail, asw3000c01v1MainGlobalFailTrapEnable, 
				asw3000c01v1ResPckBytes, asw3000c01v1ResGlobalFail, asw3000c01v1ResGlobalFailTrapEnable, asw3000c01v1MainGpiFail, asw3000c01v1MainGpiFailTrapEnable, 
				asw3000c01v1MainPresFail, asw3000c01v1MainPresFailTrapEnable, asw3000c01v1MainSyncLFail, asw3000c01v1MainSyncLFailTrapEnable, asw3000c01v1MainSyncBFail, 
				asw3000c01v1MainSyncBFailTrapEnable, asw3000c01v1MainPatErFail, asw3000c01v1MainPatErFailTrapEnable, asw3000c01v1MainPatCcFail, asw3000c01v1MainPatCcFailTrapEnable, 
				asw3000c01v1MainTraffFail, asw3000c01v1MainTraffFailTrapEnable, asw3000c01v1MainNullPFail, asw3000c01v1MainNullPFailTrapEnable, asw3000c01v1ResGpiFail, 
				asw3000c01v1ResGpiFailTrapEnable, asw3000c01v1ResPresFail, asw3000c01v1ResPresFailTrapEnable, asw3000c01v1ResSyncLFail, asw3000c01v1ResSyncLFailTrapEnable, 
				asw3000c01v1ResSyncBFail, asw3000c01v1ResSyncBFailTrapEnable, asw3000c01v1ResPatErFail, asw3000c01v1ResPatErFailTrapEnable, asw3000c01v1ResPatCcFail, 
				asw3000c01v1ResPatCcFailTrapEnable, asw3000c01v1ResTraffFail, asw3000c01v1ResTraffFailTrapEnable, asw3000c01v1ResNullPFail, asw3000c01v1ResNullPFailTrapEnable, 
				asw3000c01v1MainBitrate, asw3000c01v1ResBitrate, asw3000c01v1MainPckNull, asw3000c01v1ResPckNull, asw3000c01v1SerialNo }
			STATUS current
			DESCRIPTION
				"Module ASW3000C01V1 Group"
			::= { varGroups 241501 }

		-- 1.3.6.1.4.1.10106.2.3.1.245601
		adl3000c01v1ModuleGroup OBJECT-GROUP
			OBJECTS {adl3000c01v1Index, adl3000c01v1OutPckMode, adl3000c01v1OutPckBytes, adl3000c01v1Delay, adl3000c01v1InPckBytes, 
				adl3000c01v1NoSig, adl3000c01v1NoSync, adl3000c01v1BadPckRate, adl3000c01v1Unlock, adl3000c01v1GlobalFail, 
				adl3000c01v1GlobalFailTrapEnable, adl3000c01v1Bitrate, adl3000c01v1DelayOverflow, adl3000c01v1SerialNo }
			STATUS current
			DESCRIPTION
				"Module ADL3000C01V1 Group"
			::= { varGroups 245601 }

		-- 1.3.6.1.4.1.10106.2.3.1.247001
		hvd3000c01v1ModuleGroup OBJECT-GROUP
			OBJECTS {hvd3000c01v1Index, hvd3000c01v1DvdMode, hvd3000c01v1NoSigA, hvd3000c01v1NoSigATrapEnable, hvd3000c01v1MaxEqA, 
				hvd3000c01v1UnlockA, hvd3000c01v1UnlockATrapEnable, hvd3000c01v1NoSigB, hvd3000c01v1NoSigBTrapEnable, hvd3000c01v1MaxEqB, 
				hvd3000c01v1UnlockB, hvd3000c01v1UnlockBTrapEnable, hvd3000c01v1CableLengthA, hvd3000c01v1CableLengthB, hvd3000c01v1SerialNo }
			STATUS current
			DESCRIPTION
				"Module HVD3000C01V1 Group"
			::= { varGroups 247001 }

		-- 1.3.6.1.4.1.10106.2.3.1.247002
		hvd3000c01v2ModuleGroup OBJECT-GROUP
			OBJECTS {hvd3000c01v2Index, hvd3000c01v2DvdMode, hvd3000c01v2NoSigA, hvd3000c01v2NoSigATrapEnable, hvd3000c01v2UnlockA, 
				hvd3000c01v2UnlockATrapEnable, hvd3000c01v2NoSigB, hvd3000c01v2NoSigBTrapEnable, hvd3000c01v2UnlockB, hvd3000c01v2UnlockBTrapEnable, 
				hvd3000c01v2SerialNo }
			STATUS current
			DESCRIPTION
				"Module HVD3000C01V2 Group"
			::= { varGroups 247002 }

		-- 1.3.6.1.4.1.10106.2.3.1.247101
		hdt3000c01v1ModuleGroup OBJECT-GROUP
			OBJECTS {hdt3000c01v1Index, hdt3000c01v1NoSigA, hdt3000c01v1NoSigATrapEnable, hdt3000c01v1UnlockA, hdt3000c01v1UnlockATrapEnable, 
				hdt3000c01v1LaserFailA, hdt3000c01v1LaserFailATrapEnable, hdt3000c01v1SdiFormatA, hdt3000c01v1NoSigB, hdt3000c01v1NoSigBTrapEnable, 
				hdt3000c01v1UnlockB, hdt3000c01v1UnlockBTrapEnable, hdt3000c01v1LaserFailB, hdt3000c01v1LaserFailBTrapEnable, hdt3000c01v1SdiFormatB, 
				hdt3000c01v1SerialNo }
			STATUS current
			DESCRIPTION
				"Module HDT3000C01V1 Group"
			::= { varGroups 247101 }

		-- 1.3.6.1.4.1.10106.2.3.1.247201
		hdr3000c01v1ModuleGroup OBJECT-GROUP
			OBJECTS {hdr3000c01v1Index, hdr3000c01v1InputSelA, hdr3000c01v1InputSelB, hdr3000c01v1NoSigEA, hdr3000c01v1NoSigEATrapEnable, 
				hdr3000c01v1LowPowerA, hdr3000c01v1NoSigEOA, hdr3000c01v1NoSigEOATrapEnable, hdr3000c01v1UnlockA, hdr3000c01v1UnlockATrapEnable, 
				hdr3000c01v1SdiFormatA, hdr3000c01v1NoSigEB, hdr3000c01v1NoSigEBTrapEnable, hdr3000c01v1LowPowerB, hdr3000c01v1NoSigOB, 
				hdr3000c01v1NoSigOBTrapEnable, hdr3000c01v1UnlockB, hdr3000c01v1UnlockBTrapEnable, hdr3000c01v1SdiFormatB, hdr3000c01v1SerialNo }
			STATUS current
			DESCRIPTION
				"Module HDR3000C01V1 Group"
			::= { varGroups 247201 }

		-- 1.3.6.1.4.1.10106.2.3.1.259501
		dli3001c01v1ModuleGroup OBJECT-GROUP
			OBJECTS {dli3001c01v1Index, dli3001c01v1ActivePreset, dli3001c01v1LoadPreset, dli3001c01v1SavePreset, dli3001c01v1PgmInsLogo1, 
				dli3001c01v1PgmInsLogo2, dli3001c01v1PgmInsLogo3, dli3001c01v1PgmInsLogo4, dli3001c01v1PvwInsLogo1, dli3001c01v1PvwInsLogo2, 
				dli3001c01v1PvwInsLogo3, dli3001c01v1PvwInsLogo4, dli3001c01v1MixAudio, dli3001c01v1RestartAudio, dli3001c01v1SelLogo1, 
				dli3001c01v1SelLogo2, dli3001c01v1SelLogo3, dli3001c01v1SelLogo4, dli3001c01v1Group, dli3001c01v1InsAudio, 
				dli3001c01v1EmbedBits, dli3001c01v1CleanAudioGr1, dli3001c01v1CleanAudioGr2, dli3001c01v1CleanAudioGr3, dli3001c01v1CleanAudioGr4, 
				dli3001c01v1GpiMode, dli3001c01v1LoadLogo, dli3001c01v1PosHLogo1Msb, dli3001c01v1PosHLogo1Lsb, dli3001c01v1PosVLogo1Msb, 
				dli3001c01v1PosVLogo1Lsb, dli3001c01v1PosHLogo2Msb, dli3001c01v1PosHLogo2Lsb, dli3001c01v1PosVLogo2Msb, dli3001c01v1PosVLogo2Lsb, 
				dli3001c01v1PosHLogo3Msb, dli3001c01v1PosHLogo3Lsb, dli3001c01v1PosVLogo3Msb, dli3001c01v1PosVLogo3Lsb, dli3001c01v1PosHLogo4Msb, 
				dli3001c01v1PosHLogo4Lsb, dli3001c01v1PosVLogo4Msb, dli3001c01v1PosVLogo4Lsb, dli3001c01v1NoSig, dli3001c01v1NoSigTrapEnable, 
				dli3001c01v1EdhErr, dli3001c01v1AudioFr0Err, dli3001c01v1AudioFr0ErrTrapEnable, dli3001c01v1AudioFr1Err, dli3001c01v1AudioFr1ErrTrapEnable, 
				dli3001c01v1AudioGr1, dli3001c01v1AudioGr2, dli3001c01v1AudioGr3, dli3001c01v1AudioGr4 }
			STATUS current
			DESCRIPTION
				"Module DLI3001C01V1 Group"
			::= { varGroups 259501 }

		-- 1.3.6.1.4.1.10106.2.3.1.259601
		eap3001c01v1ModuleGroup OBJECT-GROUP
			OBJECTS {eap3001c01v1Index, eap3001c01v1ActivePreset, eap3001c01v1LoadPreset, eap3001c01v1SavePreset, eap3001c01v1InsGroupA, 
				eap3001c01v1InsAudioA, eap3001c01v1EmbedBitsA, eap3001c01v1InsGroupB, eap3001c01v1InsAudioB, eap3001c01v1EmbedBitsB, 
				eap3001c01v1RdGroupA, eap3001c01v1RdGroupB, eap3001c01v1CleanAudioGr1, eap3001c01v1CleanAudioGr2, eap3001c01v1CleanAudioGr3, 
				eap3001c01v1CleanAudioGr4, eap3001c01v1GpiMode, eap3001c01v1AuxiliarInput, eap3001c01v1GainAO1I1, eap3001c01v1PhaseAO1I1, 
				eap3001c01v1GainAO1I2, eap3001c01v1PhaseAO1I2, eap3001c01v1GainAO1I3, eap3001c01v1PhaseAO1I3, eap3001c01v1GainAO1I4, 
				eap3001c01v1PhaseAO1I4, eap3001c01v1GainAO1I5, eap3001c01v1PhaseAO1I5, eap3001c01v1GainAO1I6, eap3001c01v1PhaseAO1I6, 
				eap3001c01v1GainAO1I7, eap3001c01v1PhaseAO1I7, eap3001c01v1GainAO1I8, eap3001c01v1PhaseAO1I8, eap3001c01v1GainAO2I1, 
				eap3001c01v1PhaseAO2I1, eap3001c01v1GainAO2I2, eap3001c01v1PhaseAO2I2, eap3001c01v1GainAO2I3, eap3001c01v1PhaseAO2I3, 
				eap3001c01v1GainAO2I4, eap3001c01v1PhaseAO2I4, eap3001c01v1GainAO2I5, eap3001c01v1PhaseAO2I5, eap3001c01v1GainAO2I6, 
				eap3001c01v1PhaseAO2I6, eap3001c01v1GainAO2I7, eap3001c01v1PhaseAO2I7, eap3001c01v1GainAO2I8, eap3001c01v1PhaseAO2I8, 
				eap3001c01v1GainAO3I1, eap3001c01v1PhaseAO3I1, eap3001c01v1GainAO3I2, eap3001c01v1PhaseAO3I2, eap3001c01v1GainAO3I3, 
				eap3001c01v1PhaseAO3I3, eap3001c01v1GainAO3I4, eap3001c01v1PhaseAO3I4, eap3001c01v1GainAO3I5, eap3001c01v1PhaseAO3I5, 
				eap3001c01v1GainAO3I6, eap3001c01v1PhaseAO3I6, eap3001c01v1GainAO3I7, eap3001c01v1PhaseAO3I7, eap3001c01v1GainAO3I8, 
				eap3001c01v1PhaseAO3I8, eap3001c01v1GainAO4I1, eap3001c01v1PhaseAO4I1, eap3001c01v1GainAO4I2, eap3001c01v1PhaseAO4I2, 
				eap3001c01v1GainAO4I3, eap3001c01v1PhaseAO4I3, eap3001c01v1GainAO4I4, eap3001c01v1PhaseAO4I4, eap3001c01v1GainAO4I5, 
				eap3001c01v1PhaseAO4I5, eap3001c01v1GainAO4I6, eap3001c01v1PhaseAO4I6, eap3001c01v1GainAO4I7, eap3001c01v1PhaseAO4I7, 
				eap3001c01v1GainAO4I8, eap3001c01v1PhaseAO4I8, eap3001c01v1DelayAO1Msb, eap3001c01v1DelayAO1Lsb, eap3001c01v1DelayAO2Msb, 
				eap3001c01v1DelayAO2Lsb, eap3001c01v1DelayAO3Msb, eap3001c01v1DelayAO3Lsb, eap3001c01v1DelayAO4Msb, eap3001c01v1DelayAO4Lsb, 
				eap3001c01v1GainBO1I1, eap3001c01v1PhaseBO1I1, eap3001c01v1GainBO1I2, eap3001c01v1PhaseBO1I2, eap3001c01v1GainBO1I3, 
				eap3001c01v1PhaseBO1I3, eap3001c01v1GainBO1I4, eap3001c01v1PhaseBO1I4, eap3001c01v1GainBO1I5, eap3001c01v1PhaseBO1I5, 
				eap3001c01v1GainBO1I6, eap3001c01v1PhaseBO1I6, eap3001c01v1GainBO1I7, eap3001c01v1PhaseBO1I7, eap3001c01v1GainBO1I8, 
				eap3001c01v1PhaseBO1I8, eap3001c01v1GainBO2I1, eap3001c01v1PhaseBO2I1, eap3001c01v1GainBO2I2, eap3001c01v1PhaseBO2I2, 
				eap3001c01v1GainBO2I3, eap3001c01v1PhaseBO2I3, eap3001c01v1GainBO2I4, eap3001c01v1PhaseBO2I4, eap3001c01v1GainBO2I5, 
				eap3001c01v1PhaseBO2I5, eap3001c01v1GainBO2I6, eap3001c01v1PhaseBO2I6, eap3001c01v1GainBO2I7, eap3001c01v1PhaseBO2I7, 
				eap3001c01v1GainBO2I8, eap3001c01v1PhaseBO2I8, eap3001c01v1GainBO3I1, eap3001c01v1PhaseBO3I1, eap3001c01v1GainBO3I2, 
				eap3001c01v1PhaseBO3I2, eap3001c01v1GainBO3I3, eap3001c01v1PhaseBO3I3, eap3001c01v1GainBO3I4, eap3001c01v1PhaseBO3I4, 
				eap3001c01v1GainBO3I5, eap3001c01v1PhaseBO3I5, eap3001c01v1GainBO3I6, eap3001c01v1PhaseBO3I6, eap3001c01v1GainBO3I7, 
				eap3001c01v1PhaseBO3I7, eap3001c01v1GainBO3I8, eap3001c01v1PhaseBO3I8, eap3001c01v1GainBO4I1, eap3001c01v1PhaseBO4I1, 
				eap3001c01v1GainBO4I2, eap3001c01v1PhaseBO4I2, eap3001c01v1GainBO4I3, eap3001c01v1PhaseBO4I3, eap3001c01v1GainBO4I4, 
				eap3001c01v1PhaseBO4I4, eap3001c01v1GainBO4I5, eap3001c01v1PhaseBO4I5, eap3001c01v1GainBO4I6, eap3001c01v1PhaseBO4I6, 
				eap3001c01v1GainBO4I7, eap3001c01v1PhaseBO4I7, eap3001c01v1GainBO4I8, eap3001c01v1PhaseBO4I8, eap3001c01v1DelayBO1Msb, 
				eap3001c01v1DelayBO1Lsb, eap3001c01v1DelayBO2Msb, eap3001c01v1DelayBO2Lsb, eap3001c01v1DelayBO3Msb, eap3001c01v1DelayBO3Lsb, 
				eap3001c01v1DelayBO4Msb, eap3001c01v1DelayBO4Lsb, eap3001c01v1NoSigA, eap3001c01v1NoSigATrapEnable, eap3001c01v1EdhErrA, 
				eap3001c01v1AudioFr0ErrA, eap3001c01v1AudioFr0ErrATrapEnable, eap3001c01v1AudioFr1ErrA, eap3001c01v1AudioFr1ErrATrapEnable, eap3001c01v1AudioGr1A, 
				eap3001c01v1AudioGr2A, eap3001c01v1AudioGr3A, eap3001c01v1AudioGr4A, eap3001c01v1NoSigB, eap3001c01v1NoSigBTrapEnable, 
				eap3001c01v1EdhErrB, eap3001c01v1AudioFr0ErrB, eap3001c01v1AudioFr0ErrBTrapEnable, eap3001c01v1AudioFr1ErrB, eap3001c01v1AudioFr1ErrBTrapEnable, 
				eap3001c01v1AudioGr1B, eap3001c01v1AudioGr2B, eap3001c01v1AudioGr3B, eap3001c01v1AudioGr4B }
			STATUS current
			DESCRIPTION
				"Module EAP3001C01V1 Group"
			::= { varGroups 259601 }

		-- 1.3.6.1.4.1.10106.2.3.1.272801
		ur-3100r05v1ModuleGroup OBJECT-GROUP
			OBJECTS {ur-3100r05v1Index, ur-3100r05v1PwrFailR, ur-3100r05v1PwrFailRTrapEnable, ur-3100r05v1PwrFailL, ur-3100r05v1PwrFailLTrapEnable, 
				ur-3100r05v1VccVoltage, ur-3100r05v1SerialNo }
			STATUS current
			DESCRIPTION
				"Module UR-3100R05V1 Group"
			::= { varGroups 272801 }

		-- 1.3.6.1.4.1.10106.2.3.1.272901
		ur-3100r06v1ModuleGroup OBJECT-GROUP
			OBJECTS {ur-3100r06v1Index, ur-3100r06v1PwrFailR, ur-3100r06v1PwrFailRTrapEnable, ur-3100r06v1PwrFailL, ur-3100r06v1PwrFailLTrapEnable, 
				ur-3100r06v1VccVoltage, ur-3100r06v1SerialNo }
			STATUS current
			DESCRIPTION
				"Module UR-3100R06V1 Group"
			::= { varGroups 272901 }

		-- 1.3.6.1.4.1.10106.2.3.1.273001
		ur-3100r07v1ModuleGroup OBJECT-GROUP
			OBJECTS {ur-3100r07v1Index, ur-3100r07v1PwrFailR, ur-3100r07v1PwrFailRTrapEnable, ur-3100r07v1PwrFailL, ur-3100r07v1PwrFailLTrapEnable, 
				ur-3100r07v1VccVoltage, ur-3100r07v1SerialNo }
			STATUS current
			DESCRIPTION
				"Module UR-3100R07V1 Group"
			::= { varGroups 273001 }

		-- 1.3.6.1.4.1.10106.2.3.1.273101
		ur-3100r08v1ModuleGroup OBJECT-GROUP
			OBJECTS {ur-3100r08v1Index, ur-3100r08v1PwrFailR, ur-3100r08v1PwrFailRTrapEnable, ur-3100r08v1PwrFailL, ur-3100r08v1PwrFailLTrapEnable, 
				ur-3100r08v1VccVoltage, ur-3100r08v1SerialNo }
			STATUS current
			DESCRIPTION
				"Module UR-3100R08V1 Group"
			::= { varGroups 273101 }

		-- 1.3.6.1.4.1.10106.2.3.1.273201
		ur-3100r09v1ModuleGroup OBJECT-GROUP
			OBJECTS {ur-3100r09v1Index, ur-3100r09v1PwrFailR, ur-3100r09v1PwrFailRTrapEnable, ur-3100r09v1PwrFailL, ur-3100r09v1PwrFailLTrapEnable, 
				ur-3100r09v1VccVoltage, ur-3100r09v1SerialNo }
			STATUS current
			DESCRIPTION
				"Module UR-3100R09V1 Group"
			::= { varGroups 273201 }

		-- 1.3.6.1.4.1.10106.2.3.1.274401
		dvm3001c01v1ModuleGroup OBJECT-GROUP
			OBJECTS {dvm3001c01v1Index, dvm3001c01v1VbiPassA, dvm3001c01v1VbiPassB, dvm3001c01v1ChromaA, dvm3001c01v1ChromaB, 
				dvm3001c01v1LumaFilterA, dvm3001c01v1LumaFilterB, dvm3001c01v1CustomFilterA, dvm3001c01v1CustomFilterB, dvm3001c01v1Mode, 
				dvm3001c01v1NoSigA, dvm3001c01v1NoSigATrapEnable, dvm3001c01v1NoSigB, dvm3001c01v1NoSigBTrapEnable, dvm3001c01v1MaxEqA, 
				dvm3001c01v1MaxEqB, dvm3001c01v1UnlockA, dvm3001c01v1UnlockATrapEnable, dvm3001c01v1UnlockB, dvm3001c01v1UnlockBTrapEnable, 
				dvm3001c01v1EdhErrorA, dvm3001c01v1EdhErrorB, dvm3001c01v1EdhPresA, dvm3001c01v1EdhPresB, dvm3001c01v1FormatA, 
				dvm3001c01v1FormatB, dvm3001c01v1MuteA, dvm3001c01v1MuteB, dvm3001c01v1CableLengthA, dvm3001c01v1CableLengthB, 
				dvm3001c01v1SerialNo }
			STATUS current
			DESCRIPTION
				"Module DVM3001C01V1 Group"
			::= { varGroups 274401 }

		-- 1.3.6.1.4.1.10106.2.3.1.275101
		dsw3001c01v1ModuleGroup OBJECT-GROUP
			OBJECTS {dsw3001c01v1Index, dsw3001c01v1Mode, dsw3001c01v1ModeTrapEnable, dsw3001c01v1Output, dsw3001c01v1OutSignal, 
				dsw3001c01v1TestSignal, dsw3001c01v1Format, dsw3001c01v1Input, dsw3001c01v1InputTrapEnable, dsw3001c01v1InputChange, 
				dsw3001c01v1ExtInpMMask, dsw3001c01v1NoSigMMask, dsw3001c01v1BadFmtMMask, dsw3001c01v1EdhErrMMask, dsw3001c01v1EdhPckMMask, 
				dsw3001c01v1PatternMMask, dsw3001c01v1BlackMMask, dsw3001c01v1FreezeMMask, dsw3001c01v1ExtInpRMask, dsw3001c01v1NoSigRMask, 
				dsw3001c01v1BadFmtRMask, dsw3001c01v1EdhErrRMask, dsw3001c01v1EdhPckRMask, dsw3001c01v1PatternRMask, dsw3001c01v1BlackRMask, 
				dsw3001c01v1FreezeRMask, dsw3001c01v1PresMMask, dsw3001c01v1SilMMask, dsw3001c01v1OvlMMask, dsw3001c01v1AntiphMMask, 
				dsw3001c01v1PresRMask, dsw3001c01v1SilRMask, dsw3001c01v1OvlRMask, dsw3001c01v1AntiphRMask, dsw3001c01v1AudCh9MMask, 
				dsw3001c01v1AudCh10MMask, dsw3001c01v1AudCh11MMask, dsw3001c01v1AudCh12MMask, dsw3001c01v1AudCh13MMask, dsw3001c01v1AudCh14MMask, 
				dsw3001c01v1AudCh15MMask, dsw3001c01v1AudCh16MMask, dsw3001c01v1AudCh1MMask, dsw3001c01v1AudCh2MMask, dsw3001c01v1AudCh3MMask, 
				dsw3001c01v1AudCh4MMask, dsw3001c01v1AudCh5MMask, dsw3001c01v1AudCh6MMask, dsw3001c01v1AudCh7MMask, dsw3001c01v1AudCh8MMask, 
				dsw3001c01v1AudCh9RMask, dsw3001c01v1AudCh10RMask, dsw3001c01v1AudCh11RMask, dsw3001c01v1AudCh12RMask, dsw3001c01v1AudCh13RMask, 
				dsw3001c01v1AudCh14RMask, dsw3001c01v1AudCh15RMask, dsw3001c01v1AudCh16RMask, dsw3001c01v1AudCh1RMask, dsw3001c01v1AudCh2RMask, 
				dsw3001c01v1AudCh3RMask, dsw3001c01v1AudCh4RMask, dsw3001c01v1AudCh5RMask, dsw3001c01v1AudCh6RMask, dsw3001c01v1AudCh7RMask, 
				dsw3001c01v1AudCh8RMask, dsw3001c01v1BlckFrzTimeout, dsw3001c01v1OverloadLevel, dsw3001c01v1SilenceLevel, dsw3001c01v1SilenceTime, 
				dsw3001c01v1VideoFailM, dsw3001c01v1VideoFailMTrapEnable, dsw3001c01v1VideoFailR, dsw3001c01v1VideoFailRTrapEnable, dsw3001c01v1AudioFailM, 
				dsw3001c01v1AudioFailMTrapEnable, dsw3001c01v1AudioFailR, dsw3001c01v1AudioFailRTrapEnable, dsw3001c01v1ExtInpM, dsw3001c01v1NoSigM, 
				dsw3001c01v1BadFmtM, dsw3001c01v1EdhErrM, dsw3001c01v1EdhPckM, dsw3001c01v1PatternM, dsw3001c01v1BlackM, 
				dsw3001c01v1FreezeM, dsw3001c01v1PresM, dsw3001c01v1SilM, dsw3001c01v1OvlM, dsw3001c01v1AntiphM, 
				dsw3001c01v1ExtInpR, dsw3001c01v1NoSigR, dsw3001c01v1BadFmtR, dsw3001c01v1EdhErrR, dsw3001c01v1EdhPckR, 
				dsw3001c01v1PatternR, dsw3001c01v1BlackR, dsw3001c01v1FreezeR, dsw3001c01v1PresR, dsw3001c01v1SilR, 
				dsw3001c01v1OvlR, dsw3001c01v1AntiphR }
			STATUS current
			DESCRIPTION
				"Module DSW3001C01V1 Group"
			::= { varGroups 275101 }

		-- 1.3.6.1.4.1.10106.2.3.1.278601
		dvb3001c01v1ModuleGroup OBJECT-GROUP
			OBJECTS {dvb3001c01v1Index, dvb3001c01v1NoSigA, dvb3001c01v1NoSigATrapEnable, dvb3001c01v1MaxEqA, dvb3001c01v1NoSigB, 
				dvb3001c01v1NoSigBTrapEnable, dvb3001c01v1MaxEqB, dvb3001c01v1DvdMode, dvb3001c01v1CableLengthA, dvb3001c01v1CableLengthB, 
				dvb3001c01v1SerialNo }
			STATUS current
			DESCRIPTION
				"Module DVB3001C01V1 Group"
			::= { varGroups 278601 }

		-- 1.3.6.1.4.1.10106.2.3.1.282401
		dvm3001c02v1ModuleGroup OBJECT-GROUP
			OBJECTS {dvm3001c02v1Index, dvm3001c02v1VbiPassA, dvm3001c02v1VbiPassB, dvm3001c02v1ChromaA, dvm3001c02v1ChromaB, 
				dvm3001c02v1LumaFilterA, dvm3001c02v1LumaFilterB, dvm3001c02v1CustomFilterA, dvm3001c02v1CustomFilterB, dvm3001c02v1Mode, 
				dvm3001c02v1NoSigA, dvm3001c02v1NoSigATrapEnable, dvm3001c02v1NoSigB, dvm3001c02v1NoSigBTrapEnable, dvm3001c02v1MaxEqA, 
				dvm3001c02v1MaxEqB, dvm3001c02v1UnlockA, dvm3001c02v1UnlockATrapEnable, dvm3001c02v1UnlockB, dvm3001c02v1UnlockBTrapEnable, 
				dvm3001c02v1EdhErrorA, dvm3001c02v1EdhErrorB, dvm3001c02v1EdhPresA, dvm3001c02v1EdhPresB, dvm3001c02v1FormatA, 
				dvm3001c02v1FormatB, dvm3001c02v1MuteA, dvm3001c02v1MuteB, dvm3001c02v1CableLengthA, dvm3001c02v1CableLengthB, 
				dvm3001c02v1SerialNo }
			STATUS current
			DESCRIPTION
				"Module DVM3001C02V1 Group"
			::= { varGroups 282401 }

		-- 1.3.6.1.4.1.10106.2.3.1.283901
		dvb3001c02v1ModuleGroup OBJECT-GROUP
			OBJECTS {dvb3001c02v1Index, dvb3001c02v1NoSigA, dvb3001c02v1NoSigATrapEnable, dvb3001c02v1MaxEqA, dvb3001c02v1NoSigB, 
				dvb3001c02v1NoSigBTrapEnable, dvb3001c02v1MaxEqB, dvb3001c02v1DvdMode, dvb3001c02v1CableLengthA, dvb3001c02v1CableLengthB, 
				dvb3001c02v1SerialNo }
			STATUS current
			DESCRIPTION
				"Module DVB3001C02V1 Group"
			::= { varGroups 283901 }

		-- 1.3.6.1.4.1.10106.2.3.1.286201
		gps3002c01v1ModuleGroup OBJECT-GROUP
			OBJECTS {gps3002c01v1Index, gps3002c01v1Holdover, gps3002c01v1RedundanceMode, gps3002c01v1RedundanceModeTrapEnable, gps3002c01v1CableDelay, 
				gps3002c01v1HoldoverStat, gps3002c01v1HoldoverStatTrapEnable, gps3002c01v1MaintenanceFail, gps3002c01v1MaintenanceFailTrapEnable, gps3002c01v1OutputsMuted, 
				gps3002c01v1OutputsMutedTrapEnable, gps3002c01v11ppsDisable, gps3002c01v11ppsDisableTrapEnable, gps3002c01v1AdquisitionStat, gps3002c01v1SatRxStat, 
				gps3002c01v1AntenaStat, gps3002c01v1AntenaStatTrapEnable, gps3002c01v1SatNoFail, gps3002c01v1GpsSiteSurv, gps3002c01v1GpsTrackSats, 
				gps3002c01v1GpsVisibleSats, gps3002c01v1GpsSignalLevel, gps3002c01v1HoldoverTime, gps3002c01v1FreqDriftEst, gps3002c01v1PhaseDriftEst, 
				gps3002c01v1SerialNo }
			STATUS current
			DESCRIPTION
				"Module GPS3002C01V1 Group"
			::= { varGroups 286201 }

		-- 1.3.6.1.4.1.10106.2.3.1.290701
		gps3002c03v1ModuleGroup OBJECT-GROUP
			OBJECTS {gps3002c03v1Index, gps3002c03v1Holdover, gps3002c03v1RedundanceMode, gps3002c03v1RedundanceModeTrapEnable, gps3002c03v1CableDelay, 
				gps3002c03v1HoldoverStat, gps3002c03v1HoldoverStatTrapEnable, gps3002c03v1MaintenanceFail, gps3002c03v1MaintenanceFailTrapEnable, gps3002c03v1OutputsMuted, 
				gps3002c03v1OutputsMutedTrapEnable, gps3002c03v11ppsDisable, gps3002c03v11ppsDisableTrapEnable, gps3002c03v1AdquisitionStat, gps3002c03v1SatRxStat, 
				gps3002c03v1AntenaStat, gps3002c03v1AntenaStatTrapEnable, gps3002c03v1SatNoFail, gps3002c03v1GpsSiteSurv, gps3002c03v1GpsTrackSats, 
				gps3002c03v1GpsVisibleSats, gps3002c03v1GpsSignalLevel, gps3002c03v1HoldoverTime, gps3002c03v1FreqDriftEst, gps3002c03v1PhaseDriftEst, 
				gps3002c03v1SerialNo }
			STATUS current
			DESCRIPTION
				"Module GPS3002C03V1 Group"
			::= { varGroups 290701 }

		-- 1.3.6.1.4.1.10106.2.3.1.290901
		tsm3001c01v1ModuleGroup OBJECT-GROUP
			OBJECTS {tsm3001c01v1Index, tsm3001c01v1NoTsNat, tsm3001c01v1NoTsNatTrapEnable, tsm3001c01v1NoReplac, tsm3001c01v1NoReplacTrapEnable, 
				tsm3001c01v1BadTsidNat, tsm3001c01v1BadTsidNatTrapEnable, tsm3001c01v1FragPatNat, tsm3001c01v1FragNitNat, tsm3001c01v1FragSdtNat, 
				tsm3001c01v1FragEitNat, tsm3001c01v1NoTsReg, tsm3001c01v1NoTsRegTrapEnable, tsm3001c01v1BadTsidReg, tsm3001c01v1BadTsidRegTrapEnable, 
				tsm3001c01v1FragPatReg, tsm3001c01v1FragNitReg, tsm3001c01v1SerialNo }
			STATUS current
			DESCRIPTION
				"Module TSM3001C01V1 Group"
			::= { varGroups 290901 }

		-- 1.3.6.1.4.1.10106.2.3.1.295301
		tpg3001c01v1ModuleGroup OBJECT-GROUP
			OBJECTS {tpg3001c01v1Index, tpg3001c01v1Lines, tpg3001c01v1Genlock, tpg3001c01v1EmbedBits, tpg3001c01v1TestSignalA, 
				tpg3001c01v1ColourA, tpg3001c01v1VitcInsA, tpg3001c01v1VitcModeA, tpg3001c01v1VitcInsLineA, tpg3001c01v1SchA, 
				tpg3001c01v1EmbedA, tpg3001c01v1MuteAudA, tpg3001c01v1GroupA, tpg3001c01v1AudCh1A, tpg3001c01v1AudCh2A, 
				tpg3001c01v1AudCh3A, tpg3001c01v1AudCh4A, tpg3001c01v1TextForeColA, tpg3001c01v1TextBackColA, tpg3001c01v1TextInsModeA, 
				tpg3001c01v1TextSetA, tpg3001c01v1WhiteLineA, tpg3001c01v1FrameDelayA, tpg3001c01v1VDelayA, tpg3001c01v1HDelayA, 
				tpg3001c01v1HDelayFineA, tpg3001c01v1TestSignalB, tpg3001c01v1ColourB, tpg3001c01v1VitcInsB, tpg3001c01v1VitcModeB, 
				tpg3001c01v1VitcInsLineB, tpg3001c01v1SchB, tpg3001c01v1EmbedB, tpg3001c01v1MuteAudB, tpg3001c01v1GroupB, 
				tpg3001c01v1AudCh1B, tpg3001c01v1AudCh2B, tpg3001c01v1AudCh3B, tpg3001c01v1AudCh4B, tpg3001c01v1TextForeColB, 
				tpg3001c01v1TextBackColB, tpg3001c01v1TextInsModeB, tpg3001c01v1TextSetB, tpg3001c01v1WhiteLineB, tpg3001c01v1FrameDelayB, 
				tpg3001c01v1VDelayB, tpg3001c01v1HDelayB, tpg3001c01v1HDelayFineB, tpg3001c01v1OsdSet1L8Ch1, tpg3001c01v1OsdSet1L8Ch2, 
				tpg3001c01v1OsdSet1L8Ch3, tpg3001c01v1OsdSet1L8Ch4, tpg3001c01v1OsdSet1L8Ch5, tpg3001c01v1OsdSet1L8Ch6, tpg3001c01v1OsdSet1L8Ch7, 
				tpg3001c01v1OsdSet1L8Ch8, tpg3001c01v1OsdSet1L8Ch9, tpg3001c01v1OsdSet1L8Ch10, tpg3001c01v1OsdSet1L8Ch11, tpg3001c01v1OsdSet1L8Ch12, 
				tpg3001c01v1OsdSet1L8Ch13, tpg3001c01v1OsdSet1L8Ch14, tpg3001c01v1OsdSet1L8Ch15, tpg3001c01v1OsdSet1L8Ch16, tpg3001c01v1OsdSet2L8Ch1, 
				tpg3001c01v1OsdSet2L8Ch2, tpg3001c01v1OsdSet2L8Ch3, tpg3001c01v1OsdSet2L8Ch4, tpg3001c01v1OsdSet2L8Ch5, tpg3001c01v1OsdSet2L8Ch6, 
				tpg3001c01v1OsdSet2L8Ch7, tpg3001c01v1OsdSet2L8Ch8, tpg3001c01v1OsdSet2L8Ch9, tpg3001c01v1OsdSet2L8Ch10, tpg3001c01v1OsdSet2L8Ch11, 
				tpg3001c01v1OsdSet2L8Ch12, tpg3001c01v1OsdSet2L8Ch13, tpg3001c01v1OsdSet2L8Ch14, tpg3001c01v1OsdSet2L8Ch15, tpg3001c01v1OsdSet2L8Ch16, 
				tpg3001c01v1VitcHourOff, tpg3001c01v1VitcMinOff, tpg3001c01v1VitcSecOff, tpg3001c01v1RefPresence, tpg3001c01v1RefLock, 
				tpg3001c01v1VitcHour, tpg3001c01v1VitcMin, tpg3001c01v1VitcSec, tpg3001c01v1SerialNo }
			STATUS current
			DESCRIPTION
				"Module TPG3001C01V1 Group"
			::= { varGroups 295301 }

		-- 1.3.6.1.4.1.10106.2.3.1.308701
		aac3008c01v1ModuleGroup OBJECT-GROUP
			OBJECTS {aac3008c01v1Index, aac3008c01v1InputRef, aac3008c01v1SamplingFreq, aac3008c01v1Bits, aac3008c01v1Mode, 
				aac3008c01v1FixDelay1, aac3008c01v1FixDelay2, aac3008c01v1FixDelay3, aac3008c01v1FixDelay4, aac3008c01v1GainAes1A, 
				aac3008c01v1PhaseAes1A, aac3008c01v1GainAes1B, aac3008c01v1PhaseAes1B, aac3008c01v1GainAes2A, aac3008c01v1PhaseAes2A, 
				aac3008c01v1GainAes2B, aac3008c01v1PhaseAes2B, aac3008c01v1GainAes3A, aac3008c01v1PhaseAes3A, aac3008c01v1GainAes3B, 
				aac3008c01v1PhaseAes3B, aac3008c01v1GainAes4A, aac3008c01v1PhaseAes4A, aac3008c01v1GainAes4B, aac3008c01v1PhaseAes4B, 
				aac3008c01v1MuteAes1A, aac3008c01v1MuteAes1B, aac3008c01v1MuteAes2A, aac3008c01v1MuteAes2B, aac3008c01v1MuteAes3A, 
				aac3008c01v1MuteAes3B, aac3008c01v1MuteAes4A, aac3008c01v1MuteAes4B, aac3008c01v1InputLevel, aac3008c01v1OvldLevel, 
				aac3008c01v1LockVid, aac3008c01v1LockAes, aac3008c01v1LockWclk, aac3008c01v1VarDelay, aac3008c01v1ClipCh1, 
				aac3008c01v1OvlCh1, aac3008c01v1ClipCh2, aac3008c01v1OvlCh2, aac3008c01v1ClipCh3, aac3008c01v1OvlCh3, 
				aac3008c01v1ClipCh4, aac3008c01v1OvlCh4, aac3008c01v1PeakLevOut1A, aac3008c01v1PeakLevOut1B, aac3008c01v1PeakLevOut2A, 
				aac3008c01v1PeakLevOut2B, aac3008c01v1PeakLevOut3A, aac3008c01v1PeakLevOut3B, aac3008c01v1PeakLevOut4A, aac3008c01v1PeakLevOut4B, 
				aac3008c01v1SerialNo, aac3008c01v1Det525, aac3008c01v1Det625, aac3008c01v1AesDetFreq, aac3008c01v1WclkDetFreq }
			STATUS current
			DESCRIPTION
				"Module AAC3008C01V1 Group"
			::= { varGroups 308701 }

		-- 1.3.6.1.4.1.10106.2.3.1.315301
		dsw3000c05v1ModuleGroup OBJECT-GROUP
			OBJECTS {dsw3000c05v1Index, dsw3000c05v1Mode, dsw3000c05v1ModeTrapEnable, dsw3000c05v1Buzzer, dsw3000c05v1Input, 
				dsw3000c05v1InputTrapEnable, dsw3000c05v1MainFail, dsw3000c05v1MainFailTrapEnable, dsw3000c05v1ExtMainFail, dsw3000c05v1ExtMainFailTrapEnable, 
				dsw3000c05v1ResFail, dsw3000c05v1ResFailTrapEnable, dsw3000c05v1ExtResFail, dsw3000c05v1ExtResFailTrapEnable, dsw3000c05v1AuxFail, 
				dsw3000c05v1AuxFailTrapEnable, dsw3000c05v1ExtAuxFail, dsw3000c05v1ExtAuxFailTrapEnable }
			STATUS current
			DESCRIPTION
				"Module DSW3000C05V1 Group"
			::= { varGroups 315301 }

		-- 1.3.6.1.4.1.10106.2.3.1.316801
		ssw3000c01v1ModuleGroup OBJECT-GROUP
			OBJECTS {ssw3000c01v1Index, ssw3000c01v1Mode, ssw3000c01v1ModeTrapEnable, ssw3000c01v1Buzzer, ssw3000c01v1DvbTMode, 
				ssw3000c01v1DvbTModeTrapEnable, ssw3000c01v1Input, ssw3000c01v1InputTrapEnable, ssw3000c01v1InputChange, ssw3000c01v1OutDelay, 
				ssw3000c01v1OutDelayTrapEnable, ssw3000c01v1MainFail, ssw3000c01v1MainFailTrapEnable, ssw3000c01v1ExtMainFail, ssw3000c01v1ExtMainFailTrapEnable, 
				ssw3000c01v1ResFail, ssw3000c01v1ResFailTrapEnable, ssw3000c01v1ExtResFail, ssw3000c01v1ExtResFailTrapEnable, ssw3000c01v1AuxFail, 
				ssw3000c01v1AuxFailTrapEnable, ssw3000c01v1ExtAuxFail, ssw3000c01v1ExtAuxFailTrapEnable, ssw3000c01v11ppsFail, ssw3000c01v11ppsFailTrapEnable, 
				ssw3000c01v1MainResSeam, ssw3000c01v1ResAuxSeam, ssw3000c01v1MainAuxSeam, ssw3000c01v1GlobalSeam, ssw3000c01v1GlobalSeamTrapEnable, 
				ssw3000c01v1MainDelay, ssw3000c01v1ResDelay, ssw3000c01v1AuxDelay, ssw3000c01v1SerialNo }
			STATUS current
			DESCRIPTION
				"Module SSW3000C01V1 Group"
			::= { varGroups 316801 }

		-- 1.3.6.1.4.1.10106.2.3.1.320501
		pdc3002c01v1ModuleGroup OBJECT-GROUP
			OBJECTS {pdc3002c01v1Index, pdc3002c01v1BlackA, pdc3002c01v1OutOnFailA, pdc3002c01v1LinesA, pdc3002c01v1BlackB, 
				pdc3002c01v1OutOnFailB, pdc3002c01v1LinesB, pdc3002c01v1UnlockA, pdc3002c01v1UnlockATrapEnable, pdc3002c01v1UnlockB, 
				pdc3002c01v1UnlockBTrapEnable, pdc3002c01v1NoSigA, pdc3002c01v1NoSigATrapEnable, pdc3002c01v1NoSigB, pdc3002c01v1NoSigBTrapEnable, 
				pdc3002c01v1VpsPresA, pdc3002c01v1VpsPresB, pdc3002c01v1SerialNo }
			STATUS current
			DESCRIPTION
				"Module PDC3002C01V1 Group"
			::= { varGroups 320501 }

		-- 1.3.6.1.4.1.10106.2.3.1.324201
		vct3000c11v1ModuleGroup OBJECT-GROUP
			OBJECTS {vct3000c11v1Index, vct3000c11v1Mode, vct3000c11v1ModeTrapEnable, vct3000c11v1Buzzer, vct3000c11v1Input, 
				vct3000c11v1InputTrapEnable, vct3000c11v1InputChange, vct3000c11v1RemoteEnable, vct3000c11v1MainFail, vct3000c11v1MainFailTrapEnable, 
				vct3000c11v1ResFail, vct3000c11v1ResFailTrapEnable, vct3000c11v1AuxFail, vct3000c11v1AuxFailTrapEnable, vct3000c11v1Remote, 
				vct3000c11v1SerialNo }
			STATUS current
			DESCRIPTION
				"Module VCT3000C11V1 Group"
			::= { varGroups 324201 }

		-- 1.3.6.1.4.1.10106.2.3.1.324301
		vct3000c12v1ModuleGroup OBJECT-GROUP
			OBJECTS {vct3000c12v1Index, vct3000c12v1Mode, vct3000c12v1ModeTrapEnable, vct3000c12v1Buzzer, vct3000c12v1Input, 
				vct3000c12v1InputTrapEnable, vct3000c12v1InputChange, vct3000c12v1RemoteEnable, vct3000c12v1MainFail, vct3000c12v1MainFailTrapEnable, 
				vct3000c12v1ResFail, vct3000c12v1ResFailTrapEnable, vct3000c12v1AuxFail, vct3000c12v1AuxFailTrapEnable, vct3000c12v1Remote, 
				vct3000c12v1SerialNo }
			STATUS current
			DESCRIPTION
				"Module VCT3000C12V1 Group"
			::= { varGroups 324301 }

		-- 1.3.6.1.4.1.10106.2.3.1.324401
		vct3000c14v1ModuleGroup OBJECT-GROUP
			OBJECTS {vct3000c14v1Index, vct3000c14v1Mode, vct3000c14v1ModeTrapEnable, vct3000c14v1Buzzer, vct3000c14v1Input, 
				vct3000c14v1InputTrapEnable, vct3000c14v1InputChange, vct3000c14v1RemoteEnable, vct3000c14v1MainFail, vct3000c14v1MainFailTrapEnable, 
				vct3000c14v1ResFail, vct3000c14v1ResFailTrapEnable, vct3000c14v1AuxFail, vct3000c14v1AuxFailTrapEnable, vct3000c14v1Remote, 
				vct3000c14v1SerialNo }
			STATUS current
			DESCRIPTION
				"Module VCT3000C14V1 Group"
			::= { varGroups 324401 }

		-- 1.3.6.1.4.1.10106.2.3.1.324501
		vct3000c15v1ModuleGroup OBJECT-GROUP
			OBJECTS {vct3000c15v1Index, vct3000c15v1Mode, vct3000c15v1ModeTrapEnable, vct3000c15v1Buzzer, vct3000c15v1Input, 
				vct3000c15v1InputTrapEnable, vct3000c15v1InputChange, vct3000c15v1RemoteEnable, vct3000c15v1MainFail, vct3000c15v1MainFailTrapEnable, 
				vct3000c15v1ResFail, vct3000c15v1ResFailTrapEnable, vct3000c15v1AuxFail, vct3000c15v1AuxFailTrapEnable, vct3000c15v1Remote, 
				vct3000c15v1SerialNo }
			STATUS current
			DESCRIPTION
				"Module VCT3000C15V1 Group"
			::= { varGroups 324501 }

		-- 1.3.6.1.4.1.10106.2.3.1.327001
		vtl3000c01v1ModuleGroup OBJECT-GROUP
			OBJECTS {vtl3000c01v1Index, vtl3000c01v1VitcRdLine, vtl3000c01v1NoSignal, vtl3000c01v1NoSignalTrapEnable, vtl3000c01v1VitcOk, 
				vtl3000c01v1VitcHour, vtl3000c01v1VitcMin, vtl3000c01v1VitcSec, vtl3000c01v1VitcFrame, vtl3000c01v1StatReset, 
				vtl3000c01v1DupTc, vtl3000c01v1DupTcTrapEnable, vtl3000c01v1LostTc, vtl3000c01v1LostTcTrapEnable, vtl3000c01v1NoTcFrame, 
				vtl3000c01v1NoTcFrameTrapEnable, vtl3000c01v1StatMinutes }
			STATUS current
			DESCRIPTION
				"Module VTL3000C01V1 Group"
			::= { varGroups 327001 }

		-- 1.3.6.1.4.1.10106.2.3.1.328401
		tle3001c01v1ModuleGroup OBJECT-GROUP
			OBJECTS {tle3001c01v1Index, tle3001c01v1Serial485232, tle3001c01v1ConsoleEna, tle3001c01v1Gpo1, tle3001c01v1Gpo2, 
				tle3001c01v1Gpo3, tle3001c01v1Gpo4, tle3001c01v1InvertGpi1Pol, tle3001c01v1InvertGpi2Pol, tle3001c01v1InvertGpi3Pol, 
				tle3001c01v1InvertGpi4Pol, tle3001c01v1InvertGpo1Pol, tle3001c01v1InvertGpo2Pol, tle3001c01v1InvertGpo3Pol, tle3001c01v1InvertGpo4Pol, 
				tle3001c01v1Gpi1, tle3001c01v1Gpi1TrapEnable, tle3001c01v1Gpi2, tle3001c01v1Gpi2TrapEnable, tle3001c01v1Gpi3, 
				tle3001c01v1Gpi3TrapEnable, tle3001c01v1Gpi4, tle3001c01v1Gpi4TrapEnable, tle3001c01v1RedBoard, tle3001c01v1RedBoardTrapEnable, 
				tle3001c01v1EthLink, tle3001c01v1EthLinkTrapEnable, tle3001c01v1EthRedAct, tle3001c01v1EthRedActTrapEnable, tle3001c01v1App1Ena, 
				tle3001c01v1App2Ena, tle3001c01v1App3Ena, tle3001c01v1App4Ena, tle3001c01v1App5Ena, tle3001c01v1App6Ena, 
				tle3001c01v1App7Ena, tle3001c01v1App8Ena, tle3001c01v1App9Ena, tle3001c01v1App10Ena, tle3001c01v1App11Ena, 
				tle3001c01v1App12Ena, tle3001c01v1App13Ena, tle3001c01v1App14Ena, tle3001c01v1App15Ena, tle3001c01v1App16Ena, 
				tle3001c01v1SerialNo }
			STATUS current
			DESCRIPTION
				"Module TLE3001C01V1 Group"
			::= { varGroups 328401 }

		-- 1.3.6.1.4.1.10106.2.3.1.339901
		gvd3000c01v1ModuleGroup OBJECT-GROUP
			OBJECTS {gvd3000c01v1Index, gvd3000c01v1SignalType, gvd3000c01v1G703Type, gvd3000c01v1LosA, gvd3000c01v1LosATrapEnable, 
				gvd3000c01v1AisA, gvd3000c01v1AisATrapEnable, gvd3000c01v1LosB, gvd3000c01v1LosBTrapEnable, gvd3000c01v1AisB, 
				gvd3000c01v1AisBTrapEnable, gvd3000c01v1SerialNo }
			STATUS current
			DESCRIPTION
				"Module GVD3000C01V1 Group"
			::= { varGroups 339901 }

		-- 1.3.6.1.4.1.10106.2.3.1.343901
		htg3000c01v1ModuleGroup OBJECT-GROUP
			OBJECTS {htg3000c01v1Index, htg3000c01v1AnaRefOutFmt, htg3000c01v1DigOutFmt, htg3000c01v1ColourDis, htg3000c01v1EdhDis, 
				htg3000c01v1Smpte352Dis, htg3000c01v1GenlockMode, htg3000c01v1HDelayMain, htg3000c01v1VDelayMain, htg3000c01v1HDelayAux, 
				htg3000c01v1VDelayAux, htg3000c01v1TestSignal, htg3000c01v1RefLckFail, htg3000c01v1RefLckFailTrapEnable, htg3000c01v1RefFail, 
				htg3000c01v1RefFailTrapEnable, htg3000c01v1AnaRefPres, htg3000c01v1DigRefPres, htg3000c01v1IntRefPres, htg3000c01v1IncRefMain, 
				htg3000c01v1IncRefAux, htg3000c01v1DigRefFmt, htg3000c01v1SerialNo }
			STATUS current
			DESCRIPTION
				"Module HTG3000C01V1 Group"
			::= { varGroups 343901 }

		-- 1.3.6.1.4.1.10106.2.3.1.347601
		hvd3001c01v1ModuleGroup OBJECT-GROUP
			OBJECTS {hvd3001c01v1Index, hvd3001c01v1OpElecNA, hvd3001c01v1OpElecNB, hvd3001c01v1Mode, hvd3001c01v1NoSigA, 
				hvd3001c01v1NoSigATrapEnable, hvd3001c01v1UnlockA, hvd3001c01v1UnlockATrapEnable, hvd3001c01v1LFailA, hvd3001c01v1LFailATrapEnable, 
				hvd3001c01v1HdA, hvd3001c01v1NoElecA, hvd3001c01v1NoOpticA, hvd3001c01v1NoSigB, hvd3001c01v1NoSigBTrapEnable, 
				hvd3001c01v1UnlockB, hvd3001c01v1UnlockBTrapEnable, hvd3001c01v1LFailB, hvd3001c01v1LFailBTrapEnable, hvd3001c01v1HdB, 
				hvd3001c01v1NoElecB, hvd3001c01v1NoOpticB, hvd3001c01v1OpTxPres, hvd3001c01v1OpRxPres, hvd3001c01v1SfpTxSn, 
				hvd3001c01v1SfpRxSn, hvd3001c01v1SerialNo }
			STATUS current
			DESCRIPTION
				"Module HVD3001C01V1 Group"
			::= { varGroups 347601 }

		-- 1.3.6.1.4.1.10106.2.3.1.350401
		vct3000c13v1ModuleGroup OBJECT-GROUP
			OBJECTS {vct3000c13v1Index, vct3000c13v1Mode, vct3000c13v1ModeTrapEnable, vct3000c13v1Buzzer, vct3000c13v1Input, 
				vct3000c13v1InputTrapEnable, vct3000c13v1InputChange, vct3000c13v1RemoteEnable, vct3000c13v1MainFail, vct3000c13v1MainFailTrapEnable, 
				vct3000c13v1ResFail, vct3000c13v1ResFailTrapEnable, vct3000c13v1AuxFail, vct3000c13v1AuxFailTrapEnable, vct3000c13v1Remote, 
				vct3000c13v1SerialNo }
			STATUS current
			DESCRIPTION
				"Module VCT3000C13V1 Group"
			::= { varGroups 350401 }

		-- 1.3.6.1.4.1.10106.2.3.1.352201
		dad3002c02v1ModuleGroup OBJECT-GROUP
			OBJECTS {dad3002c02v1Index, dad3002c02v1LosA, dad3002c02v1LosATrapEnable, dad3002c02v1LosB, dad3002c02v1LosBTrapEnable, 
				dad3002c02v1SerialNo }
			STATUS current
			DESCRIPTION
				"Module DAD3002C02V1 Group"
			::= { varGroups 352201 }

		-- 1.3.6.1.4.1.10106.2.3.1.353101
		hvd3001c02v1ModuleGroup OBJECT-GROUP
			OBJECTS {hvd3001c02v1Index, hvd3001c02v1OpElecNA, hvd3001c02v1OpElecNB, hvd3001c02v1Mode, hvd3001c02v1NoSigA, 
				hvd3001c02v1NoSigATrapEnable, hvd3001c02v1UnlockA, hvd3001c02v1UnlockATrapEnable, hvd3001c02v1LFailA, hvd3001c02v1LFailATrapEnable, 
				hvd3001c02v1HdA, hvd3001c02v1NoElecA, hvd3001c02v1NoOpticA, hvd3001c02v1NoSigB, hvd3001c02v1NoSigBTrapEnable, 
				hvd3001c02v1UnlockB, hvd3001c02v1UnlockBTrapEnable, hvd3001c02v1LFailB, hvd3001c02v1LFailBTrapEnable, hvd3001c02v1HdB, 
				hvd3001c02v1NoElecB, hvd3001c02v1NoOpticB, hvd3001c02v1OpTxPres, hvd3001c02v1OpRxPres, hvd3001c02v1SfpTxSn, 
				hvd3001c02v1SfpRxSn, hvd3001c02v1SerialNo }
			STATUS current
			DESCRIPTION
				"Module HVD3001C02V1 Group"
			::= { varGroups 353101 }

		-- 1.3.6.1.4.1.10106.2.3.1.357101
		hvd3001c03v1ModuleGroup OBJECT-GROUP
			OBJECTS {hvd3001c03v1Index, hvd3001c03v1OpElecNA, hvd3001c03v1OpElecNB, hvd3001c03v1Mode, hvd3001c03v1NoSigA, 
				hvd3001c03v1NoSigATrapEnable, hvd3001c03v1UnlockA, hvd3001c03v1UnlockATrapEnable, hvd3001c03v1LFailA, hvd3001c03v1LFailATrapEnable, 
				hvd3001c03v1HdA, hvd3001c03v1NoElecA, hvd3001c03v1NoOpticA, hvd3001c03v1NoSigB, hvd3001c03v1NoSigBTrapEnable, 
				hvd3001c03v1UnlockB, hvd3001c03v1UnlockBTrapEnable, hvd3001c03v1LFailB, hvd3001c03v1LFailBTrapEnable, hvd3001c03v1HdB, 
				hvd3001c03v1NoElecB, hvd3001c03v1NoOpticB, hvd3001c03v1OpTxPres, hvd3001c03v1OpRxPres, hvd3001c03v1SfpTxSn, 
				hvd3001c03v1SfpRxSn, hvd3001c03v1SerialNo }
			STATUS current
			DESCRIPTION
				"Module HVD3001C03V1 Group"
			::= { varGroups 357101 }

		-- 1.3.6.1.4.1.10106.2.3.1.357201
		hvd3001c04v1ModuleGroup OBJECT-GROUP
			OBJECTS {hvd3001c04v1Index, hvd3001c04v1OpElecNA, hvd3001c04v1OpElecNB, hvd3001c04v1Mode, hvd3001c04v1NoSigA, 
				hvd3001c04v1NoSigATrapEnable, hvd3001c04v1UnlockA, hvd3001c04v1UnlockATrapEnable, hvd3001c04v1LFailA, hvd3001c04v1LFailATrapEnable, 
				hvd3001c04v1HdA, hvd3001c04v1NoElecA, hvd3001c04v1NoOpticA, hvd3001c04v1NoSigB, hvd3001c04v1NoSigBTrapEnable, 
				hvd3001c04v1UnlockB, hvd3001c04v1UnlockBTrapEnable, hvd3001c04v1LFailB, hvd3001c04v1LFailBTrapEnable, hvd3001c04v1HdB, 
				hvd3001c04v1NoElecB, hvd3001c04v1NoOpticB, hvd3001c04v1OpTxPres, hvd3001c04v1OpRxPres, hvd3001c04v1SfpTxSn, 
				hvd3001c04v1SfpRxSn, hvd3001c04v1SerialNo }
			STATUS current
			DESCRIPTION
				"Module HVD3001C04V1 Group"
			::= { varGroups 357201 }

		-- 1.3.6.1.4.1.10106.2.3.1.357501
		hfs3000c01v1ModuleGroup OBJECT-GROUP
			OBJECTS {hfs3000c01v1Index, hfs3000c01v1SynchroModeA, hfs3000c01v1FailModeA, hfs3000c01v1VbiModeA, hfs3000c01v1DelayModeA, 
				hfs3000c01v1SynchroModeB, hfs3000c01v1FailModeB, hfs3000c01v1VbiModeB, hfs3000c01v1DelayModeB, hfs3000c01v1HDelayA, 
				hfs3000c01v1FrameDelayA, hfs3000c01v1VDelayA, hfs3000c01v1LumaGainA, hfs3000c01v1ChromaGainA, hfs3000c01v1BlackOffsetA, 
				hfs3000c01v1HDelayB, hfs3000c01v1FrameDelayB, hfs3000c01v1VDelayB, hfs3000c01v1LumaGainB, hfs3000c01v1ChromaGainB, 
				hfs3000c01v1BlackOffsetB, hfs3000c01v1NoSigA, hfs3000c01v1NoSigATrapEnable, hfs3000c01v1UnlockA, hfs3000c01v1UnlockATrapEnable, 
				hfs3000c01v1EdhCrcA, hfs3000c01v1EdhCrcATrapEnable, hfs3000c01v1GpiFailA, hfs3000c01v1GpiFailATrapEnable, hfs3000c01v1NoSigB, 
				hfs3000c01v1NoSigBTrapEnable, hfs3000c01v1UnlockB, hfs3000c01v1UnlockBTrapEnable, hfs3000c01v1EdhCrcB, hfs3000c01v1EdhCrcBTrapEnable, 
				hfs3000c01v1GpiFailB, hfs3000c01v1GpiFailBTrapEnable, hfs3000c01v1NoRef, hfs3000c01v1NoRefTrapEnable, hfs3000c01v1RefAUnlock, 
				hfs3000c01v1RefAUnlockTrapEnable, hfs3000c01v1RefBUnlock, hfs3000c01v1RefBUnlockTrapEnable, hfs3000c01v1InputFormat, hfs3000c01v1SdiFormatA, 
				hfs3000c01v1SdiFormatB, hfs3000c01v1SigDelayA, hfs3000c01v1SigDelayB, hfs3000c01v1SerialNo }
			STATUS current
			DESCRIPTION
				"Module HFS3000C01V1 Group"
			::= { varGroups 357501 }

		-- 1.3.6.1.4.1.10106.2.3.1.357502
		hfs3000c01v2ModuleGroup OBJECT-GROUP
			OBJECTS {hfs3000c01v2Index, hfs3000c01v2SynchroModeA, hfs3000c01v2FailModeA, hfs3000c01v2VbiModeA, hfs3000c01v2DelayModeA, 
				hfs3000c01v2SynchroModeB, hfs3000c01v2FailModeB, hfs3000c01v2VbiModeB, hfs3000c01v2DelayModeB, hfs3000c01v2HDelayA, 
				hfs3000c01v2FrameDelayA, hfs3000c01v2VDelayA, hfs3000c01v2LumaGainA, hfs3000c01v2ChromaGainA, hfs3000c01v2BlackOffsetA, 
				hfs3000c01v2HDelayB, hfs3000c01v2FrameDelayB, hfs3000c01v2VDelayB, hfs3000c01v2LumaGainB, hfs3000c01v2ChromaGainB, 
				hfs3000c01v2BlackOffsetB, hfs3000c01v2ClnGr1A, hfs3000c01v2ClnGr2A, hfs3000c01v2ClnGr3A, hfs3000c01v2ClnGr4A, 
				hfs3000c01v2BitsA, hfs3000c01v2Grp1P0A, hfs3000c01v2Grp1P1A, hfs3000c01v2Grp2P0A, hfs3000c01v2Grp2P1A, 
				hfs3000c01v2Grp3P0A, hfs3000c01v2Grp3P1A, hfs3000c01v2Grp4P0A, hfs3000c01v2Grp4P1A, hfs3000c01v2ClnGr1B, 
				hfs3000c01v2ClnGr2B, hfs3000c01v2ClnGr3B, hfs3000c01v2ClnGr4B, hfs3000c01v2BitsB, hfs3000c01v2Grp1P0B, 
				hfs3000c01v2Grp1P1B, hfs3000c01v2Grp2P0B, hfs3000c01v2Grp2P1B, hfs3000c01v2Grp3P0B, hfs3000c01v2Grp3P1B, 
				hfs3000c01v2Grp4P0B, hfs3000c01v2Grp4P1B, hfs3000c01v2NoSigA, hfs3000c01v2NoSigATrapEnable, hfs3000c01v2UnlockA, 
				hfs3000c01v2UnlockATrapEnable, hfs3000c01v2EdhCrcA, hfs3000c01v2EdhCrcATrapEnable, hfs3000c01v2GpiFailA, hfs3000c01v2GpiFailATrapEnable, 
				hfs3000c01v2NoSigB, hfs3000c01v2NoSigBTrapEnable, hfs3000c01v2UnlockB, hfs3000c01v2UnlockBTrapEnable, hfs3000c01v2EdhCrcB, 
				hfs3000c01v2EdhCrcBTrapEnable, hfs3000c01v2GpiFailB, hfs3000c01v2GpiFailBTrapEnable, hfs3000c01v2NoRef, hfs3000c01v2NoRefTrapEnable, 
				hfs3000c01v2RefAUnlock, hfs3000c01v2RefAUnlockTrapEnable, hfs3000c01v2RefBUnlock, hfs3000c01v2RefBUnlockTrapEnable, hfs3000c01v2InputFormat, 
				hfs3000c01v2SdiFormatA, hfs3000c01v2SdiFormatB, hfs3000c01v2SigDelayA, hfs3000c01v2SigDelayB, hfs3000c01v2Grp1APres, 
				hfs3000c01v2Grp2APres, hfs3000c01v2Grp3APres, hfs3000c01v2Grp4APres, hfs3000c01v2Grp1BPres, hfs3000c01v2Grp2BPres, 
				hfs3000c01v2Grp3BPres, hfs3000c01v2Grp4BPres, hfs3000c01v2Grp1P0AErr, hfs3000c01v2Grp1P1AErr, hfs3000c01v2Grp2P0AErr, 
				hfs3000c01v2Grp2P1AErr, hfs3000c01v2Grp3P0AErr, hfs3000c01v2Grp3P1AErr, hfs3000c01v2Grp4P0AErr, hfs3000c01v2Grp4P1AErr, 
				hfs3000c01v2Grp1P0BErr, hfs3000c01v2Grp1P1BErr, hfs3000c01v2Grp2P0BErr, hfs3000c01v2Grp2P1BErr, hfs3000c01v2Grp3P0BErr, 
				hfs3000c01v2Grp3P1BErr, hfs3000c01v2Grp4P0BErr, hfs3000c01v2Grp4P1BErr, hfs3000c01v2SerialNo }
			STATUS current
			DESCRIPTION
				"Module HFS3000C01V2 Group"
			::= { varGroups 357502 }

		-- 1.3.6.1.4.1.10106.2.3.1.358101
		hde3000c01v1ModuleGroup OBJECT-GROUP
			OBJECTS {hde3000c01v1Index, hde3000c01v1RestorPreset, hde3000c01v1ActivePreset, hde3000c01v1LoadPreset, hde3000c01v1SavePreset, 
				hde3000c01v1ClnGr1A, hde3000c01v1ClnGr2A, hde3000c01v1ClnGr3A, hde3000c01v1ClnGr4A, hde3000c01v1ClnGr1B, 
				hde3000c01v1ClnGr2B, hde3000c01v1ClnGr3B, hde3000c01v1ClnGr4B, hde3000c01v1Grp1P0A, hde3000c01v1Grp1P1A, 
				hde3000c01v1Grp2P0A, hde3000c01v1Grp2P1A, hde3000c01v1Grp3P0A, hde3000c01v1Grp3P1A, hde3000c01v1Grp4P0A, 
				hde3000c01v1Grp4P1A, hde3000c01v1Grp1P0B, hde3000c01v1Grp1P1B, hde3000c01v1Grp2P0B, hde3000c01v1Grp2P1B, 
				hde3000c01v1Grp3P0B, hde3000c01v1Grp3P1B, hde3000c01v1Grp4P0B, hde3000c01v1Grp4P1B, hde3000c01v1Aes1A, 
				hde3000c01v1Aes2A, hde3000c01v1Aes3A, hde3000c01v1Aes4A, hde3000c01v1Aes1B, hde3000c01v1Aes2B, 
				hde3000c01v1Aes3B, hde3000c01v1Aes4B, hde3000c01v1OvldLevel, hde3000c01v1SilenceLevel, hde3000c01v1SilenceTime, 
				hde3000c01v1DelayMode, hde3000c01v1DelaySteps, hde3000c01v1Grp1P0AGain, hde3000c01v1Grp1P1AGain, hde3000c01v1Grp2P0AGain, 
				hde3000c01v1Grp2P1AGain, hde3000c01v1Grp3P0AGain, hde3000c01v1Grp3P1AGain, hde3000c01v1Grp4P0AGain, hde3000c01v1Grp4P1AGain, 
				hde3000c01v1Grp1P0BGain, hde3000c01v1Grp1P1BGain, hde3000c01v1Grp2P0BGain, hde3000c01v1Grp2P1BGain, hde3000c01v1Grp3P0BGain, 
				hde3000c01v1Grp3P1BGain, hde3000c01v1Grp4P0BGain, hde3000c01v1Grp4P1BGain, hde3000c01v1Aes1AGain, hde3000c01v1Aes2AGain, 
				hde3000c01v1Aes3AGain, hde3000c01v1Aes4AGain, hde3000c01v1Aes1BGain, hde3000c01v1Aes2BGain, hde3000c01v1Aes3BGain, 
				hde3000c01v1Aes4BGain, hde3000c01v1Grp1P0ADelay, hde3000c01v1Grp1P1ADelay, hde3000c01v1Grp2P0ADelay, hde3000c01v1Grp2P1ADelay, 
				hde3000c01v1Grp3P0ADelay, hde3000c01v1Grp3P1ADelay, hde3000c01v1Grp4P0ADelay, hde3000c01v1Grp4P1ADelay, hde3000c01v1Grp1P0BDelay, 
				hde3000c01v1Grp1P1BDelay, hde3000c01v1Grp2P0BDelay, hde3000c01v1Grp2P1BDelay, hde3000c01v1Grp3P0BDelay, hde3000c01v1Grp3P1BDelay, 
				hde3000c01v1Grp4P0BDelay, hde3000c01v1Grp4P1BDelay, hde3000c01v1Aes1ADelay, hde3000c01v1Aes2ADelay, hde3000c01v1Aes3ADelay, 
				hde3000c01v1Aes4ADelay, hde3000c01v1Aes1BDelay, hde3000c01v1Aes2BDelay, hde3000c01v1Aes3BDelay, hde3000c01v1Aes4BDelay, 
				hde3000c01v1NoSignalA, hde3000c01v1NoSignalATrapEnable, hde3000c01v1UnlockA, hde3000c01v1UnlockATrapEnable, hde3000c01v1EdhErrorA, 
				hde3000c01v1EdhErrorATrapEnable, hde3000c01v1AesFailA, hde3000c01v1AesFailATrapEnable, hde3000c01v1DeemFailA, hde3000c01v1DeemFailATrapEnable, 
				hde3000c01v1AesOvlA, hde3000c01v1AesOvlATrapEnable, hde3000c01v1DeemOvlA, hde3000c01v1DeemOvlATrapEnable, hde3000c01v1FormatA, 
				hde3000c01v1NoSignalB, hde3000c01v1NoSignalBTrapEnable, hde3000c01v1UnlockB, hde3000c01v1UnlockBTrapEnable, hde3000c01v1EdhErrorB, 
				hde3000c01v1EdhErrorBTrapEnable, hde3000c01v1AesFailB, hde3000c01v1AesFailBTrapEnable, hde3000c01v1DeemFailB, hde3000c01v1DeemFailBTrapEnable, 
				hde3000c01v1AesOvlB, hde3000c01v1AesOvlBTrapEnable, hde3000c01v1DeemOvlB, hde3000c01v1DeemOvlBTrapEnable, hde3000c01v1FormatB, 
				hde3000c01v1SerialNo, hde3000c01v1CorteSelChB }
			STATUS current
			DESCRIPTION
				"Module HDE3000C01V1 Group"
			::= { varGroups 358101 }

		-- 1.3.6.1.4.1.10106.2.3.1.359901
		hae3000c01v1ModuleGroup OBJECT-GROUP
			OBJECTS {hae3000c01v1Index, hae3000c01v1RestorPreset, hae3000c01v1ActivePreset, hae3000c01v1LoadPreset, hae3000c01v1SavePreset, 
				hae3000c01v1ClnGr1A, hae3000c01v1ClnGr2A, hae3000c01v1ClnGr3A, hae3000c01v1ClnGr4A, hae3000c01v1ClnGr1B, 
				hae3000c01v1ClnGr2B, hae3000c01v1ClnGr3B, hae3000c01v1ClnGr4B, hae3000c01v1Grp1P0A, hae3000c01v1Grp1P1A, 
				hae3000c01v1Grp2P0A, hae3000c01v1Grp2P1A, hae3000c01v1Grp3P0A, hae3000c01v1Grp3P1A, hae3000c01v1Grp4P0A, 
				hae3000c01v1Grp4P1A, hae3000c01v1Grp1P0B, hae3000c01v1Grp1P1B, hae3000c01v1Grp2P0B, hae3000c01v1Grp2P1B, 
				hae3000c01v1Grp3P0B, hae3000c01v1Grp3P1B, hae3000c01v1Grp4P0B, hae3000c01v1Grp4P1B, hae3000c01v1FullScaleLev, 
				hae3000c01v1SamplingClkA, hae3000c01v1SamplingClkB, hae3000c01v1OvldLevel, hae3000c01v1SilenceLevel, hae3000c01v1SilenceTime, 
				hae3000c01v1DelayMode, hae3000c01v1DelaySteps, hae3000c01v1Grp1P0AGain, hae3000c01v1Grp1P1AGain, hae3000c01v1Grp2P0AGain, 
				hae3000c01v1Grp2P1AGain, hae3000c01v1Grp3P0AGain, hae3000c01v1Grp3P1AGain, hae3000c01v1Grp4P0AGain, hae3000c01v1Grp4P1AGain, 
				hae3000c01v1Grp1P0BGain, hae3000c01v1Grp1P1BGain, hae3000c01v1Grp2P0BGain, hae3000c01v1Grp2P1BGain, hae3000c01v1Grp3P0BGain, 
				hae3000c01v1Grp3P1BGain, hae3000c01v1Grp4P0BGain, hae3000c01v1Grp4P1BGain, hae3000c01v1Grp1P0ADelay, hae3000c01v1Grp1P1ADelay, 
				hae3000c01v1Grp2P0ADelay, hae3000c01v1Grp2P1ADelay, hae3000c01v1Grp3P0ADelay, hae3000c01v1Grp3P1ADelay, hae3000c01v1Grp4P0ADelay, 
				hae3000c01v1Grp4P1ADelay, hae3000c01v1Grp1P0BDelay, hae3000c01v1Grp1P1BDelay, hae3000c01v1Grp2P0BDelay, hae3000c01v1Grp2P1BDelay, 
				hae3000c01v1Grp3P0BDelay, hae3000c01v1Grp3P1BDelay, hae3000c01v1Grp4P0BDelay, hae3000c01v1Grp4P1BDelay, hae3000c01v1NoSignalA, 
				hae3000c01v1NoSignalATrapEnable, hae3000c01v1UnlockA, hae3000c01v1UnlockATrapEnable, hae3000c01v1EdhErrorA, hae3000c01v1EdhErrorATrapEnable, 
				hae3000c01v1AesFailA, hae3000c01v1AesFailATrapEnable, hae3000c01v1DeemFailA, hae3000c01v1DeemFailATrapEnable, hae3000c01v1DeemOvlA, 
				hae3000c01v1DeemOvlATrapEnable, hae3000c01v1ClippingA, hae3000c01v1ClippingATrapEnable, hae3000c01v1FormatA, hae3000c01v1NoSignalB, 
				hae3000c01v1NoSignalBTrapEnable, hae3000c01v1UnlockB, hae3000c01v1UnlockBTrapEnable, hae3000c01v1EdhErrorB, hae3000c01v1EdhErrorBTrapEnable, 
				hae3000c01v1AesFailB, hae3000c01v1AesFailBTrapEnable, hae3000c01v1DeemFailB, hae3000c01v1DeemFailBTrapEnable, hae3000c01v1DeemOvlB, 
				hae3000c01v1DeemOvlBTrapEnable, hae3000c01v1ClippingB, hae3000c01v1ClippingBTrapEnable, hae3000c01v1FormatB, hae3000c01v1SerialNo, 
				hae3000c01v1CorteSelChB }
			STATUS current
			DESCRIPTION
				"Module HAE3000C01V1 Group"
			::= { varGroups 359901 }

		-- 1.3.6.1.4.1.10106.2.3.1.360001
		had3000c01v1ModuleGroup OBJECT-GROUP
			OBJECTS {had3000c01v1Index, had3000c01v1RestorPreset, had3000c01v1ActivePreset, had3000c01v1LoadPreset, had3000c01v1SavePreset, 
				had3000c01v1ClnGr1A, had3000c01v1ClnGr2A, had3000c01v1ClnGr3A, had3000c01v1ClnGr4A, had3000c01v1ClnGr1B, 
				had3000c01v1ClnGr2B, had3000c01v1ClnGr3B, had3000c01v1ClnGr4B, had3000c01v1Grp1P0A, had3000c01v1Grp1P1A, 
				had3000c01v1Grp2P0A, had3000c01v1Grp2P1A, had3000c01v1Grp3P0A, had3000c01v1Grp3P1A, had3000c01v1Grp4P0A, 
				had3000c01v1Grp4P1A, had3000c01v1Grp1P0B, had3000c01v1Grp1P1B, had3000c01v1Grp2P0B, had3000c01v1Grp2P1B, 
				had3000c01v1Grp3P0B, had3000c01v1Grp3P1B, had3000c01v1Grp4P0B, had3000c01v1Grp4P1B, had3000c01v1Aes1A, 
				had3000c01v1Aes2A, had3000c01v1Aes1B, had3000c01v1Aes2B, had3000c01v1FullScaleLev, had3000c01v1SamplingClkA, 
				had3000c01v1SamplingClkB, had3000c01v1OvldLevel, had3000c01v1SilenceLevel, had3000c01v1SilenceTime, had3000c01v1DelayMode, 
				had3000c01v1DelaySteps, had3000c01v1Grp1P0AGain, had3000c01v1Grp1P1AGain, had3000c01v1Grp2P0AGain, had3000c01v1Grp2P1AGain, 
				had3000c01v1Grp3P0AGain, had3000c01v1Grp3P1AGain, had3000c01v1Grp4P0AGain, had3000c01v1Grp4P1AGain, had3000c01v1Grp1P0BGain, 
				had3000c01v1Grp1P1BGain, had3000c01v1Grp2P0BGain, had3000c01v1Grp2P1BGain, had3000c01v1Grp3P0BGain, had3000c01v1Grp3P1BGain, 
				had3000c01v1Grp4P0BGain, had3000c01v1Grp4P1BGain, had3000c01v1Aes1AGain, had3000c01v1Aes2AGain, had3000c01v1Aes1BGain, 
				had3000c01v1Aes2BGain, had3000c01v1Grp1P0ADelay, had3000c01v1Grp1P1ADelay, had3000c01v1Grp2P0ADelay, had3000c01v1Grp2P1ADelay, 
				had3000c01v1Grp3P0ADelay, had3000c01v1Grp3P1ADelay, had3000c01v1Grp4P0ADelay, had3000c01v1Grp4P1ADelay, had3000c01v1Grp1P0BDelay, 
				had3000c01v1Grp1P1BDelay, had3000c01v1Grp2P0BDelay, had3000c01v1Grp2P1BDelay, had3000c01v1Grp3P0BDelay, had3000c01v1Grp3P1BDelay, 
				had3000c01v1Grp4P0BDelay, had3000c01v1Grp4P1BDelay, had3000c01v1Aes1ADelay, had3000c01v1Aes2ADelay, had3000c01v1Aes1BDelay, 
				had3000c01v1Aes2BDelay, had3000c01v1NoSignalA, had3000c01v1NoSignalATrapEnable, had3000c01v1UnlockA, had3000c01v1UnlockATrapEnable, 
				had3000c01v1EdhErrorA, had3000c01v1EdhErrorATrapEnable, had3000c01v1SampRFailA, had3000c01v1SampRFailATrapEnable, had3000c01v1DeemFailA, 
				had3000c01v1DeemFailATrapEnable, had3000c01v1AesOvlA, had3000c01v1AesOvlATrapEnable, had3000c01v1DeemOvlA, had3000c01v1DeemOvlATrapEnable, 
				had3000c01v1FormatA, had3000c01v1NoSignalB, had3000c01v1NoSignalBTrapEnable, had3000c01v1UnlockB, had3000c01v1UnlockBTrapEnable, 
				had3000c01v1EdhErrorB, had3000c01v1EdhErrorBTrapEnable, had3000c01v1SampRFailB, had3000c01v1SampRFailBTrapEnable, had3000c01v1DeemFailB, 
				had3000c01v1DeemFailBTrapEnable, had3000c01v1AesOvlB, had3000c01v1AesOvlBTrapEnable, had3000c01v1DeemOvlB, had3000c01v1DeemOvlBTrapEnable, 
				had3000c01v1FormatB, had3000c01v1SerialNo, had3000c01v1CorteSelChB }
			STATUS current
			DESCRIPTION
				"Module HAD3000C01V1 Group"
			::= { varGroups 360001 }

		-- 1.3.6.1.4.1.10106.2.3.1.362001
		ipa3000c01v1ModuleGroup OBJECT-GROUP
			OBJECTS {ipa3000c01v1Index, ipa3000c01v1Mode, ipa3000c01v1ModeTrapEnable, ipa3000c01v1DvbTMode, ipa3000c01v1DvbTModeTrapEnable, 
				ipa3000c01v1NarrowPllBw, ipa3000c01v1Buzzer, ipa3000c01v1SeamlessPrior, ipa3000c01v1Input, ipa3000c01v1InputTrapEnable, 
				ipa3000c01v1InputStChange, ipa3000c01v1InputChange, ipa3000c01v1EnaAsiMain, ipa3000c01v1EnaAsiRes, ipa3000c01v1EnaIpMain, 
				ipa3000c01v1EnaIpRes, ipa3000c01v1OutDelay, ipa3000c01v1OutDelayTrapEnable, ipa3000c01v1AsiMainPrior, ipa3000c01v1AsiResPrior, 
				ipa3000c01v1IpMainPrior, ipa3000c01v1IpResPrior, ipa3000c01v1StatReset, ipa3000c01v1StatSel, ipa3000c01v1StatMode, 
				ipa3000c01v1IgmpVersion, ipa3000c01v1EthMode, ipa3000c01v1PingEnable, ipa3000c01v1PacketDelay, ipa3000c01v1Str1UipDAdd3, 
				ipa3000c01v1Str1UipDAdd2, ipa3000c01v1Str1UipDAdd1, ipa3000c01v1Str1UipDAdd0, ipa3000c01v1Str1MipDAdd3, ipa3000c01v1Str1MipDAdd2, 
				ipa3000c01v1Str1MipDAdd1, ipa3000c01v1Str1MipDAdd0, ipa3000c01v1Str1DPortMsb, ipa3000c01v1Str1DPortLsb, ipa3000c01v1Str1FecEna, 
				ipa3000c01v1Str1MulticEna, ipa3000c01v1VlanRx1Enable, ipa3000c01v1VlanRx1Reg1, ipa3000c01v1VlanRx1Reg2, ipa3000c01v1Str2UipDAdd3, 
				ipa3000c01v1Str2UipDAdd2, ipa3000c01v1Str2UipDAdd1, ipa3000c01v1Str2UipDAdd0, ipa3000c01v1Str2MipDAdd3, ipa3000c01v1Str2MipDAdd2, 
				ipa3000c01v1Str2MipDAdd1, ipa3000c01v1Str2MipDAdd0, ipa3000c01v1Str2DPortMsb, ipa3000c01v1Str2DPortLsb, ipa3000c01v1Str2FecEna, 
				ipa3000c01v1Str2MulticEna, ipa3000c01v1VlanRx2Enable, ipa3000c01v1VlanRx2Reg1, ipa3000c01v1VlanRx2Reg2, ipa3000c01v1TxUniEna, 
				ipa3000c01v1TxMultiEna, ipa3000c01v1LocalIpAdd3, ipa3000c01v1LocalIpAdd2, ipa3000c01v1LocalIpAdd1, ipa3000c01v1LocalIpAdd0, 
				ipa3000c01v1LocalIpMask3, ipa3000c01v1LocalIpMask2, ipa3000c01v1LocalIpMask1, ipa3000c01v1LocalIpMask0, ipa3000c01v1LocalIpGway3, 
				ipa3000c01v1LocalIpGway2, ipa3000c01v1LocalIpGway1, ipa3000c01v1LocalIpGway0, ipa3000c01v1TxUipAdd3, ipa3000c01v1TxUipAdd2, 
				ipa3000c01v1TxUipAdd1, ipa3000c01v1TxUipAdd0, ipa3000c01v1TxMipAdd3, ipa3000c01v1TxMipAdd2, ipa3000c01v1TxMipAdd1, 
				ipa3000c01v1TxMipAdd0, ipa3000c01v1TxSPortMsb, ipa3000c01v1TxSPortLsb, ipa3000c01v1TxDPortMsb, ipa3000c01v1TxDPortLsb, 
				ipa3000c01v1VlanTxEnable, ipa3000c01v1VlanTxPriority, ipa3000c01v1VlanTxReg1, ipa3000c01v1VlanTxReg2, ipa3000c01v1TxLParam, 
				ipa3000c01v1TxFecMode, ipa3000c01v1TxDParam, ipa3000c01v1TxTspkInIppk, ipa3000c01v1TxRowDelay, ipa3000c01v1TxColDelay, 
				ipa3000c01v1LowCost, ipa3000c01v1HighReliabilty, ipa3000c01v1HighThroughput, ipa3000c01v1LowDelay, ipa3000c01v1Precedence, 
				ipa3000c01v1Ttl, ipa3000c01v11ppsFail, ipa3000c01v11ppsFailTrapEnable, ipa3000c01v110mhzFail, ipa3000c01v110mhzFailTrapEnable, 
				ipa3000c01v1OutputFail, ipa3000c01v1OutputFailTrapEnable, ipa3000c01v1AsiMainDelWar, ipa3000c01v1AsiMainDelWarTrapEnable, ipa3000c01v1AsiResDelWar, 
				ipa3000c01v1AsiResDelWarTrapEnable, ipa3000c01v1IpMainDelWar, ipa3000c01v1IpMainDelWarTrapEnable, ipa3000c01v1IpResDelWar, ipa3000c01v1IpResDelWarTrapEnable, 
				ipa3000c01v1AsiMainFail, ipa3000c01v1AsiMainFailTrapEnable, ipa3000c01v1ExAsiMainFail, ipa3000c01v1ExAsiMainFailTrapEnable, ipa3000c01v1AsiResFail, 
				ipa3000c01v1AsiResFailTrapEnable, ipa3000c01v1ExAsiResFail, ipa3000c01v1ExAsiResFailTrapEnable, ipa3000c01v1IpMainFail, ipa3000c01v1IpMainFailTrapEnable, 
				ipa3000c01v1ExIpMainFail, ipa3000c01v1ExIpMainFailTrapEnable, ipa3000c01v1IpResFail, ipa3000c01v1IpResFailTrapEnable, ipa3000c01v1ExIpResFail, 
				ipa3000c01v1ExIpResFailTrapEnable, ipa3000c01v1AsimAsirSeam, ipa3000c01v1AsimIpmSeam, ipa3000c01v1AsimIprSeam, ipa3000c01v1AsirIpmSeam, 
				ipa3000c01v1AsirIprSeam, ipa3000c01v1IpmIprSeam, ipa3000c01v1GlobalSeam, ipa3000c01v1GlobalSeamTrapEnable, ipa3000c01v1AsiMainDelay, 
				ipa3000c01v1AsiResDelay, ipa3000c01v1IpMainDelay, ipa3000c01v1IpResDelay, ipa3000c01v1IpRxAddress3, ipa3000c01v1IpRxAddress2, 
				ipa3000c01v1IpRxAddress1, ipa3000c01v1IpRxAddress0, ipa3000c01v1IpRxPort, ipa3000c01v1LParam, ipa3000c01v1FecMode, 
				ipa3000c01v1PacketSize, ipa3000c01v1DParam, ipa3000c01v1TsPckInIpPck, ipa3000c01v1PacketRate, ipa3000c01v1TimeSinceReset, 
				ipa3000c01v1LostIpPck, ipa3000c01v1RecoveredIpPck, ipa3000c01v1OutOrdIpPck, ipa3000c01v1FecRate, ipa3000c01v1Link, 
				ipa3000c01v1DestAvailable, ipa3000c01v1BufferStatus, ipa3000c01v1PingStatus, ipa3000c01v1SerialNo, ipa3000c01v1NullPckRtp, 
				ipa3000c01v1Str1IgmFAdd3, ipa3000c01v1Str1IgmFAdd2, ipa3000c01v1Str1IgmFAdd1, ipa3000c01v1Str1IgmFAdd0, ipa3000c01v1Str2IgmFAdd3, 
				ipa3000c01v1Str2IgmFAdd2, ipa3000c01v1Str2IgmFAdd1, ipa3000c01v1Str2IgmFAdd0, ipa3000c01v1EnSeamNondvbt, ipa3000c01v1IpLinkFailEn, 
				ipa3000c01v1IpDestFailEn, ipa3000c01v1System, ipa3000c01v1SpeedForce, ipa3000c01v1BadCrcPck, ipa3000c01v1InpFailMode, 
				ipa3000c01v1MaxDelayTxIp }
			STATUS current
			DESCRIPTION
				"Module IPA3000C01V1 Group"
			::= { varGroups 362001 }

		-- 1.3.6.1.4.1.10106.2.3.1.362002
		ipa3000c01v2ModuleGroup OBJECT-GROUP
			OBJECTS {ipa3000c01v2Index, ipa3000c01v2Mode, ipa3000c01v2ModeTrapEnable, ipa3000c01v2DvbTMode, ipa3000c01v2DvbTModeTrapEnable, 
				ipa3000c01v2NullPckRtp, ipa3000c01v2NarrowPllBw, ipa3000c01v2Buzzer, ipa3000c01v2SeamlessPrior, ipa3000c01v2EnSeamNondvbt, 
				ipa3000c01v2Input, ipa3000c01v2InputTrapEnable, ipa3000c01v2InputStChange, ipa3000c01v2InputChange, ipa3000c01v2EnaAsiMain, 
				ipa3000c01v2EnaAsiRes, ipa3000c01v2EnaIpMain, ipa3000c01v2EnaIpRes, ipa3000c01v2OutDelay, ipa3000c01v2OutDelayTrapEnable, 
				ipa3000c01v2AsiMainPrior, ipa3000c01v2AsiResPrior, ipa3000c01v2IpMainPrior, ipa3000c01v2IpResPrior, ipa3000c01v2StatReset, 
				ipa3000c01v2StatSel, ipa3000c01v2StatMode, ipa3000c01v2IgmpVersion, ipa3000c01v2EthMode, ipa3000c01v2PingEnable, 
				ipa3000c01v2PacketDelay, ipa3000c01v2IpLinkFailEn, ipa3000c01v2IpDestFailEn, ipa3000c01v2SpeedForce, ipa3000c01v2Str1UipDAdd3, 
				ipa3000c01v2Str1UipDAdd2, ipa3000c01v2Str1UipDAdd1, ipa3000c01v2Str1UipDAdd0, ipa3000c01v2Str1MipDAdd3, ipa3000c01v2Str1MipDAdd2, 
				ipa3000c01v2Str1MipDAdd1, ipa3000c01v2Str1MipDAdd0, ipa3000c01v2Str1DPortMsb, ipa3000c01v2Str1DPortLsb, ipa3000c01v2Str1FecEna, 
				ipa3000c01v2Str1MulticEna, ipa3000c01v2VlanRx1Enable, ipa3000c01v2VlanRx1Reg1, ipa3000c01v2VlanRx1Reg2, ipa3000c01v2Str2UipDAdd3, 
				ipa3000c01v2Str2UipDAdd2, ipa3000c01v2Str2UipDAdd1, ipa3000c01v2Str2UipDAdd0, ipa3000c01v2Str2MipDAdd3, ipa3000c01v2Str2MipDAdd2, 
				ipa3000c01v2Str2MipDAdd1, ipa3000c01v2Str2MipDAdd0, ipa3000c01v2Str2DPortMsb, ipa3000c01v2Str2DPortLsb, ipa3000c01v2Str2FecEna, 
				ipa3000c01v2Str2MulticEna, ipa3000c01v2VlanRx2Enable, ipa3000c01v2VlanRx2Reg1, ipa3000c01v2VlanRx2Reg2, ipa3000c01v2TxUniEna, 
				ipa3000c01v2TxMultiEna, ipa3000c01v2LocalIpAdd3, ipa3000c01v2LocalIpAdd2, ipa3000c01v2LocalIpAdd1, ipa3000c01v2LocalIpAdd0, 
				ipa3000c01v2LocalIpMask3, ipa3000c01v2LocalIpMask2, ipa3000c01v2LocalIpMask1, ipa3000c01v2LocalIpMask0, ipa3000c01v2LocalIpGway3, 
				ipa3000c01v2LocalIpGway2, ipa3000c01v2LocalIpGway1, ipa3000c01v2LocalIpGway0, ipa3000c01v2TxUipAdd3, ipa3000c01v2TxUipAdd2, 
				ipa3000c01v2TxUipAdd1, ipa3000c01v2TxUipAdd0, ipa3000c01v2TxMipAdd3, ipa3000c01v2TxMipAdd2, ipa3000c01v2TxMipAdd1, 
				ipa3000c01v2TxMipAdd0, ipa3000c01v2TxSPortMsb, ipa3000c01v2TxSPortLsb, ipa3000c01v2TxDPortMsb, ipa3000c01v2TxDPortLsb, 
				ipa3000c01v2VlanTxEnable, ipa3000c01v2VlanTxPriority, ipa3000c01v2VlanTxReg1, ipa3000c01v2VlanTxReg2, ipa3000c01v2TxLParam, 
				ipa3000c01v2TxFecMode, ipa3000c01v2TxDParam, ipa3000c01v2TxTspkInIppk, ipa3000c01v2TxRowDelay, ipa3000c01v2TxColDelay, 
				ipa3000c01v2LowCost, ipa3000c01v2HighReliabilty, ipa3000c01v2HighThroughput, ipa3000c01v2LowDelay, ipa3000c01v2Precedence, 
				ipa3000c01v2Ttl, ipa3000c01v2Str1IgmFAdd3, ipa3000c01v2Str1IgmFAdd2, ipa3000c01v2Str1IgmFAdd1, ipa3000c01v2Str1IgmFAdd0, 
				ipa3000c01v2Str2IgmFAdd3, ipa3000c01v2Str2IgmFAdd2, ipa3000c01v2Str2IgmFAdd1, ipa3000c01v2Str2IgmFAdd0, ipa3000c01v21ppsFail, 
				ipa3000c01v21ppsFailTrapEnable, ipa3000c01v210mhzFail, ipa3000c01v210mhzFailTrapEnable, ipa3000c01v2OutputFail, ipa3000c01v2OutputFailTrapEnable, 
				ipa3000c01v2AsiMainDelWar, ipa3000c01v2AsiMainDelWarTrapEnable, ipa3000c01v2AsiResDelWar, ipa3000c01v2AsiResDelWarTrapEnable, ipa3000c01v2IpMainDelWar, 
				ipa3000c01v2IpMainDelWarTrapEnable, ipa3000c01v2IpResDelWar, ipa3000c01v2IpResDelWarTrapEnable, ipa3000c01v2AsiMainFail, ipa3000c01v2AsiMainFailTrapEnable, 
				ipa3000c01v2ExAsiMainFail, ipa3000c01v2ExAsiMainFailTrapEnable, ipa3000c01v2AsiResFail, ipa3000c01v2AsiResFailTrapEnable, ipa3000c01v2ExAsiResFail, 
				ipa3000c01v2ExAsiResFailTrapEnable, ipa3000c01v2IpMainFail, ipa3000c01v2IpMainFailTrapEnable, ipa3000c01v2ExIpMainFail, ipa3000c01v2ExIpMainFailTrapEnable, 
				ipa3000c01v2IpResFail, ipa3000c01v2IpResFailTrapEnable, ipa3000c01v2ExIpResFail, ipa3000c01v2ExIpResFailTrapEnable, ipa3000c01v2AsimAsirSeam, 
				ipa3000c01v2AsimIpmSeam, ipa3000c01v2AsimIprSeam, ipa3000c01v2AsirIpmSeam, ipa3000c01v2AsirIprSeam, ipa3000c01v2IpmIprSeam, 
				ipa3000c01v2GlobalSeam, ipa3000c01v2GlobalSeamTrapEnable, ipa3000c01v2AsiMainDelay, ipa3000c01v2AsiResDelay, ipa3000c01v2IpMainDelay, 
				ipa3000c01v2IpResDelay, ipa3000c01v2IpRxAddress3, ipa3000c01v2IpRxAddress2, ipa3000c01v2IpRxAddress1, ipa3000c01v2IpRxAddress0, 
				ipa3000c01v2IpRxPort, ipa3000c01v2LParam, ipa3000c01v2FecMode, ipa3000c01v2PacketSize, ipa3000c01v2DParam, 
				ipa3000c01v2TsPckInIpPck, ipa3000c01v2PacketRate, ipa3000c01v2TimeSinceReset, ipa3000c01v2LostIpPck, ipa3000c01v2RecoveredIpPck, 
				ipa3000c01v2BadCrcPck, ipa3000c01v2OutOrdIpPck, ipa3000c01v2FecRate, ipa3000c01v2Link, ipa3000c01v2System, 
				ipa3000c01v2DestAvailable, ipa3000c01v2BufferStatus, ipa3000c01v2PingStatus, ipa3000c01v2SerialNo, ipa3000c01v2InpFailMode, 
				ipa3000c01v2MaxDelayTxIp }
			STATUS current
			DESCRIPTION
				"Module IPA3000C01V2 Group"
			::= { varGroups 362002 }

		-- 1.3.6.1.4.1.10106.2.3.1.364801
		hsw3000c01v1ModuleGroup OBJECT-GROUP
			OBJECTS {hsw3000c01v1Index, hsw3000c01v1ActivePreset, hsw3000c01v1LoadPreset, hsw3000c01v1SavePreset, hsw3000c01v1StateSel, 
				hsw3000c01v1StateSelTrapEnable, hsw3000c01v1SwitchMode, hsw3000c01v1SwitchModeTrapEnable, hsw3000c01v1FreezeMode, hsw3000c01v1BypassEnable, 
				hsw3000c01v1BypassEnableTrapEnable, hsw3000c01v1InpFailMode, hsw3000c01v1OperatingMode, hsw3000c01v1OperatingModeTrapEnable, hsw3000c01v1StateAMap, 
				hsw3000c01v1StateBMap, hsw3000c01v1StateAGpo, hsw3000c01v1StateBGpo, hsw3000c01v1AnaRefFmt, hsw3000c01v1In1StChange, 
				hsw3000c01v1In2StChange, hsw3000c01v1Gpi1StChange, hsw3000c01v1Gpi2StChange, hsw3000c01v1InputChange, hsw3000c01v1VDelay, 
				hsw3000c01v1HDelay, hsw3000c01v1Holdoff, hsw3000c01v1PhyFailTim, hsw3000c01v1FmtFailTim, hsw3000c01v1IncFailTim, 
				hsw3000c01v1GpiFailTim, hsw3000c01v1BlkFailTim, hsw3000c01v1FrzFailTim, hsw3000c01v1PatFailTim, hsw3000c01v1CrcFailTim, 
				hsw3000c01v1ActPer1, hsw3000c01v1DeactPer1, hsw3000c01v1ActPer2, hsw3000c01v1DeactPer2, hsw3000c01v1CrcThreshold, 
				hsw3000c01v1BlackThreshold, hsw3000c01v1VertFrozenWin, hsw3000c01v1HtalFrozenWin, hsw3000c01v1In1PhyFailMsk, hsw3000c01v1In1FmtFailMsk, 
				hsw3000c01v1In1IncFailMsk, hsw3000c01v1In1GpiFailMsk, hsw3000c01v1In1BlkFailMsk, hsw3000c01v1In1FrzFailMsk, hsw3000c01v1In1PatFailMsk, 
				hsw3000c01v1In1CrcFailMsk, hsw3000c01v1In2PhyFailMsk, hsw3000c01v1In2FmtFailMsk, hsw3000c01v1In2IncFailMsk, hsw3000c01v1In2GpiFailMsk, 
				hsw3000c01v1In2BlkFailMsk, hsw3000c01v1In2FrzFailMsk, hsw3000c01v1In2PatFailMsk, hsw3000c01v1In2CrcFailMsk, hsw3000c01v1RefFailMsk, 
				hsw3000c01v1LockFailMsk, hsw3000c01v1In1Fail, hsw3000c01v1In1FailTrapEnable, hsw3000c01v1In2Fail, hsw3000c01v1In2FailTrapEnable, 
				hsw3000c01v1In1ExtFail, hsw3000c01v1In1ExtFailTrapEnable, hsw3000c01v1In2ExtFail, hsw3000c01v1In2ExtFailTrapEnable, hsw3000c01v1BlindExtFail, 
				hsw3000c01v1BlindExtFailTrapEnable, hsw3000c01v1SelOut1, hsw3000c01v1SelOut1TrapEnable, hsw3000c01v1SelOut2, hsw3000c01v1SelOut2TrapEnable, 
				hsw3000c01v1Gpi3Stat, hsw3000c01v1Gpi3StatTrapEnable, hsw3000c01v1In1PhyFail, hsw3000c01v1In1PhyFailTrapEnable, hsw3000c01v1In1FmtFail, 
				hsw3000c01v1In1FmtFailTrapEnable, hsw3000c01v1In1IncFail, hsw3000c01v1In1IncFailTrapEnable, hsw3000c01v1In1GpiFail, hsw3000c01v1In1GpiFailTrapEnable, 
				hsw3000c01v1In1BlkFail, hsw3000c01v1In1BlkFailTrapEnable, hsw3000c01v1In1FrzFail, hsw3000c01v1In1FrzFailTrapEnable, hsw3000c01v1In1PatFail, 
				hsw3000c01v1In1PatFailTrapEnable, hsw3000c01v1In1CrcFail, hsw3000c01v1In1CrcFailTrapEnable, hsw3000c01v1In2PhyFail, hsw3000c01v1In2PhyFailTrapEnable, 
				hsw3000c01v1In2FmtFail, hsw3000c01v1In2FmtFailTrapEnable, hsw3000c01v1In2IncFail, hsw3000c01v1In2IncFailTrapEnable, hsw3000c01v1In2GpiFail, 
				hsw3000c01v1In2GpiFailTrapEnable, hsw3000c01v1In2BlkFail, hsw3000c01v1In2BlkFailTrapEnable, hsw3000c01v1In2FrzFail, hsw3000c01v1In2FrzFailTrapEnable, 
				hsw3000c01v1In2PatFail, hsw3000c01v1In2PatFailTrapEnable, hsw3000c01v1In2CrcFail, hsw3000c01v1In2CrcFailTrapEnable, hsw3000c01v1RefFail, 
				hsw3000c01v1RefFailTrapEnable, hsw3000c01v1LockFail, hsw3000c01v1LockFailTrapEnable, hsw3000c01v1BliGpiFail, hsw3000c01v1In1Format, 
				hsw3000c01v1In2Format, hsw3000c01v1RefFormat, hsw3000c01v1SerialNo, hsw3000c01v1Gpi3StChange }
			STATUS current
			DESCRIPTION
				"Module HSW3000C01V1 Group"
			::= { varGroups 364801 }

		-- 1.3.6.1.4.1.10106.2.3.1.364802
		hsw3000c01v2ModuleGroup OBJECT-GROUP
			OBJECTS {hsw3000c01v2Index, hsw3000c01v2ActivePreset, hsw3000c01v2LoadPreset, hsw3000c01v2SavePreset, hsw3000c01v2StateSel, 
				hsw3000c01v2StateSelTrapEnable, hsw3000c01v2SwitchMode, hsw3000c01v2SwitchModeTrapEnable, hsw3000c01v2FreezeMode, hsw3000c01v2BypassEnable, 
				hsw3000c01v2BypassEnableTrapEnable, hsw3000c01v2InpFailMode, hsw3000c01v2OperatingMode, hsw3000c01v2OperatingModeTrapEnable, hsw3000c01v2StateAMap, 
				hsw3000c01v2StateBMap, hsw3000c01v2StateAGpo, hsw3000c01v2StateBGpo, hsw3000c01v2AnaRefFmt, hsw3000c01v2In1StChange, 
				hsw3000c01v2In2StChange, hsw3000c01v2Gpi1StChange, hsw3000c01v2Gpi2StChange, hsw3000c01v2Gpi3StChange, hsw3000c01v2InputChange, 
				hsw3000c01v2VDelay, hsw3000c01v2HDelay, hsw3000c01v2Holdoff, hsw3000c01v2PhyFailTim, hsw3000c01v2FmtFailTim, 
				hsw3000c01v2IncFailTim, hsw3000c01v2GpiFailTim, hsw3000c01v2BlkFailTim, hsw3000c01v2FrzFailTim, hsw3000c01v2PatFailTim, 
				hsw3000c01v2CrcFailTim, hsw3000c01v2SilFailTim, hsw3000c01v2OvrFailTim, hsw3000c01v2PhFailTim, hsw3000c01v2PresFailTim, 
				hsw3000c01v2ActPer1, hsw3000c01v2DeactPer1, hsw3000c01v2ActPer2, hsw3000c01v2DeactPer2, hsw3000c01v2CrcThreshold, 
				hsw3000c01v2BlackThreshold, hsw3000c01v2VertFrozenWin, hsw3000c01v2HtalFrozenWin, hsw3000c01v2In1PhyFailMsk, hsw3000c01v2In1FmtFailMsk, 
				hsw3000c01v2In1IncFailMsk, hsw3000c01v2In1GpiFailMsk, hsw3000c01v2In1BlkFailMsk, hsw3000c01v2In1FrzFailMsk, hsw3000c01v2In1PatFailMsk, 
				hsw3000c01v2In1CrcFailMsk, hsw3000c01v2In1SilFailMsk, hsw3000c01v2In1OvrFailMsk, hsw3000c01v2In1PhFailMsk, hsw3000c01v2In1PreFailMsk, 
				hsw3000c01v2In2PhyFailMsk, hsw3000c01v2In2FmtFailMsk, hsw3000c01v2In2IncFailMsk, hsw3000c01v2In2GpiFailMsk, hsw3000c01v2In2BlkFailMsk, 
				hsw3000c01v2In2FrzFailMsk, hsw3000c01v2In2PatFailMsk, hsw3000c01v2In2CrcFailMsk, hsw3000c01v2In2SilFailMsk, hsw3000c01v2In2OvrFailMsk, 
				hsw3000c01v2In2PhFailMsk, hsw3000c01v2In2PreFailMsk, hsw3000c01v2RefFailMsk, hsw3000c01v2LockFailMsk, hsw3000c01v2In1AudG1p0En, 
				hsw3000c01v2In1AudG1p1En, hsw3000c01v2In1AudG2p0En, hsw3000c01v2In1AudG2p1En, hsw3000c01v2In1AudG3p0En, hsw3000c01v2In1AudG3p1En, 
				hsw3000c01v2In1AudG4p0En, hsw3000c01v2In1AudG4p1En, hsw3000c01v2In2AudG1p0En, hsw3000c01v2In2AudG1p1En, hsw3000c01v2In2AudG2p0En, 
				hsw3000c01v2In2AudG2p1En, hsw3000c01v2In2AudG3p0En, hsw3000c01v2In2AudG3p1En, hsw3000c01v2In2AudG4p0En, hsw3000c01v2In2AudG4p1En, 
				hsw3000c01v2SilenceLevel, hsw3000c01v2SilenceTime, hsw3000c01v2OverloadLevel, hsw3000c01v2In1Fail, hsw3000c01v2In1FailTrapEnable, 
				hsw3000c01v2In2Fail, hsw3000c01v2In2FailTrapEnable, hsw3000c01v2In1ExtFail, hsw3000c01v2In1ExtFailTrapEnable, hsw3000c01v2In2ExtFail, 
				hsw3000c01v2In2ExtFailTrapEnable, hsw3000c01v2BlindExtFail, hsw3000c01v2BlindExtFailTrapEnable, hsw3000c01v2SelOut1, hsw3000c01v2SelOut1TrapEnable, 
				hsw3000c01v2SelOut2, hsw3000c01v2SelOut2TrapEnable, hsw3000c01v2Gpi3Stat, hsw3000c01v2Gpi3StatTrapEnable, hsw3000c01v2In1PhyFail, 
				hsw3000c01v2In1PhyFailTrapEnable, hsw3000c01v2In1FmtFail, hsw3000c01v2In1FmtFailTrapEnable, hsw3000c01v2In1IncFail, hsw3000c01v2In1IncFailTrapEnable, 
				hsw3000c01v2In1GpiFail, hsw3000c01v2In1GpiFailTrapEnable, hsw3000c01v2In1BlkFail, hsw3000c01v2In1BlkFailTrapEnable, hsw3000c01v2In1FrzFail, 
				hsw3000c01v2In1FrzFailTrapEnable, hsw3000c01v2In1PatFail, hsw3000c01v2In1PatFailTrapEnable, hsw3000c01v2In1CrcFail, hsw3000c01v2In1CrcFailTrapEnable, 
				hsw3000c01v2In1SilFail, hsw3000c01v2In1SilFailTrapEnable, hsw3000c01v2In1OvrFail, hsw3000c01v2In1OvrFailTrapEnable, hsw3000c01v2In1PhFail, 
				hsw3000c01v2In1PhFailTrapEnable, hsw3000c01v2In1PreFail, hsw3000c01v2In1PreFailTrapEnable, hsw3000c01v2In2PhyFail, hsw3000c01v2In2PhyFailTrapEnable, 
				hsw3000c01v2In2FmtFail, hsw3000c01v2In2FmtFailTrapEnable, hsw3000c01v2In2IncFail, hsw3000c01v2In2IncFailTrapEnable, hsw3000c01v2In2GpiFail, 
				hsw3000c01v2In2GpiFailTrapEnable, hsw3000c01v2In2BlkFail, hsw3000c01v2In2BlkFailTrapEnable, hsw3000c01v2In2FrzFail, hsw3000c01v2In2FrzFailTrapEnable, 
				hsw3000c01v2In2PatFail, hsw3000c01v2In2PatFailTrapEnable, hsw3000c01v2In2CrcFail, hsw3000c01v2In2CrcFailTrapEnable, hsw3000c01v2In2SilFail, 
				hsw3000c01v2In2SilFailTrapEnable, hsw3000c01v2In2OvrFail, hsw3000c01v2In2OvrFailTrapEnable, hsw3000c01v2In2PhFail, hsw3000c01v2In2PhFailTrapEnable, 
				hsw3000c01v2In2PreFail, hsw3000c01v2In2PreFailTrapEnable, hsw3000c01v2RefFail, hsw3000c01v2RefFailTrapEnable, hsw3000c01v2LockFail, 
				hsw3000c01v2LockFailTrapEnable, hsw3000c01v2BliGpiFail, hsw3000c01v2In1Format, hsw3000c01v2In1FormatTrapEnable, hsw3000c01v2In2Format, 
				hsw3000c01v2In2FormatTrapEnable, hsw3000c01v2RefFormat, hsw3000c01v2RefFormatTrapEnable, hsw3000c01v2SerialNo, hsw3000c01v2SynchroModeIn1, 
				hsw3000c01v2SynchroModeIn2, hsw3000c01v2StatusMode, hsw3000c01v2EqualPid, hsw3000c01v2EqualPidTrapEnable, hsw3000c01v2EqualUmid, 
				hsw3000c01v2EqualUmidTrapEnable, hsw3000c01v2In1PidPres, hsw3000c01v2In2PidPres, hsw3000c01v2In1UmidPres, hsw3000c01v2In2UmidPres, 
				hsw3000c01v2In1Grp1Pres, hsw3000c01v2In1Grp1PresTrapEnable, hsw3000c01v2In1Grp2Pres, hsw3000c01v2In1Grp2PresTrapEnable, hsw3000c01v2In1Grp3Pres, 
				hsw3000c01v2In1Grp3PresTrapEnable, hsw3000c01v2In1Grp4Pres, hsw3000c01v2In1Grp4PresTrapEnable, hsw3000c01v2In1Grp1P0Err, hsw3000c01v2In1Grp1P0ErrTrapEnable, 
				hsw3000c01v2In1Grp1P1Err, hsw3000c01v2In1Grp1P1ErrTrapEnable, hsw3000c01v2In1Grp2P0Err, hsw3000c01v2In1Grp2P0ErrTrapEnable, hsw3000c01v2In1Grp2P1Err, 
				hsw3000c01v2In1Grp2P1ErrTrapEnable, hsw3000c01v2In1Grp3P0Err, hsw3000c01v2In1Grp3P0ErrTrapEnable, hsw3000c01v2In1Grp3P1Err, hsw3000c01v2In1Grp3P1ErrTrapEnable, 
				hsw3000c01v2In1Grp4P0Err, hsw3000c01v2In1Grp4P0ErrTrapEnable, hsw3000c01v2In1Grp4P1Err, hsw3000c01v2In1Grp4P1ErrTrapEnable, hsw3000c01v2In2Grp1Pres, 
				hsw3000c01v2In2Grp1PresTrapEnable, hsw3000c01v2In2Grp2Pres, hsw3000c01v2In2Grp2PresTrapEnable, hsw3000c01v2In2Grp3Pres, hsw3000c01v2In2Grp3PresTrapEnable, 
				hsw3000c01v2In2Grp4Pres, hsw3000c01v2In2Grp4PresTrapEnable, hsw3000c01v2In2Grp1P0Err, hsw3000c01v2In2Grp1P0ErrTrapEnable, hsw3000c01v2In2Grp1P1Err, 
				hsw3000c01v2In2Grp1P1ErrTrapEnable, hsw3000c01v2In2Grp2P0Err, hsw3000c01v2In2Grp2P0ErrTrapEnable, hsw3000c01v2In2Grp2P1Err, hsw3000c01v2In2Grp2P1ErrTrapEnable, 
				hsw3000c01v2In2Grp3P0Err, hsw3000c01v2In2Grp3P0ErrTrapEnable, hsw3000c01v2In2Grp3P1Err, hsw3000c01v2In2Grp3P1ErrTrapEnable, hsw3000c01v2In2Grp4P0Err, 
				hsw3000c01v2In2Grp4P0ErrTrapEnable, hsw3000c01v2In2Grp4P1Err, hsw3000c01v2In2Grp4P1ErrTrapEnable }
			STATUS current
			DESCRIPTION
				"Module HSW3000C01V2 Group"
			::= { varGroups 364802 }

		-- 1.3.6.1.4.1.10106.2.3.1.364803
		hsw3000c01v3ModuleGroup OBJECT-GROUP
			OBJECTS {hsw3000c01v3Index, hsw3000c01v3ActivePreset, hsw3000c01v3LoadPreset, hsw3000c01v3SavePreset, hsw3000c01v3StateSel, 
				hsw3000c01v3StateSelTrapEnable, hsw3000c01v3SwitchMode, hsw3000c01v3SwitchModeTrapEnable, hsw3000c01v3FreezeMode, hsw3000c01v3BypassEnable, 
				hsw3000c01v3BypassEnableTrapEnable, hsw3000c01v3InpFailMode, hsw3000c01v3OperatingMode, hsw3000c01v3OperatingModeTrapEnable, hsw3000c01v3StateAMap, 
				hsw3000c01v3StateBMap, hsw3000c01v3StateAGpo, hsw3000c01v3StateBGpo, hsw3000c01v3AnaRefFmt, hsw3000c01v3In1StChange, 
				hsw3000c01v3In2StChange, hsw3000c01v3Gpi1StChange, hsw3000c01v3Gpi2StChange, hsw3000c01v3Gpi3StChange, hsw3000c01v3InputChange, 
				hsw3000c01v3VDelay, hsw3000c01v3HDelay, hsw3000c01v3Holdoff, hsw3000c01v3PhyFailTim, hsw3000c01v3FmtFailTim, 
				hsw3000c01v3IncFailTim, hsw3000c01v3StatusMode, hsw3000c01v3SynchroModeIn1, hsw3000c01v3SynchroModeIn2, hsw3000c01v3GpiFailTim, 
				hsw3000c01v3BlkFailTim, hsw3000c01v3FrzFailTim, hsw3000c01v3PatFailTim, hsw3000c01v3CrcFailTim, hsw3000c01v3SilFailTim, 
				hsw3000c01v3OvrFailTim, hsw3000c01v3PhFailTim, hsw3000c01v3PresFailTim, hsw3000c01v3ActPer1, hsw3000c01v3DeactPer1, 
				hsw3000c01v3ActPer2, hsw3000c01v3DeactPer2, hsw3000c01v3CrcThreshold, hsw3000c01v3BlackThreshold, hsw3000c01v3VertFrozenWin, 
				hsw3000c01v3HtalFrozenWin, hsw3000c01v3In1PhyFailMsk, hsw3000c01v3In1FmtFailMsk, hsw3000c01v3In1IncFailMsk, hsw3000c01v3In1GpiFailMsk, 
				hsw3000c01v3In1BlkFailMsk, hsw3000c01v3In1FrzFailMsk, hsw3000c01v3In1PatFailMsk, hsw3000c01v3In1CrcFailMsk, hsw3000c01v3In1SilFailMsk, 
				hsw3000c01v3In1OvrFailMsk, hsw3000c01v3In1PhFailMsk, hsw3000c01v3In1PreFailMsk, hsw3000c01v3In2PhyFailMsk, hsw3000c01v3In2FmtFailMsk, 
				hsw3000c01v3In2IncFailMsk, hsw3000c01v3In2GpiFailMsk, hsw3000c01v3In2BlkFailMsk, hsw3000c01v3In2FrzFailMsk, hsw3000c01v3In2PatFailMsk, 
				hsw3000c01v3In2CrcFailMsk, hsw3000c01v3In2SilFailMsk, hsw3000c01v3In2OvrFailMsk, hsw3000c01v3In2PhFailMsk, hsw3000c01v3In2PreFailMsk, 
				hsw3000c01v3RefFailMsk, hsw3000c01v3LockFailMsk, hsw3000c01v3In1AudG1p0Msk, hsw3000c01v3In1AudG1p1Msk, hsw3000c01v3In1AudG2p0Msk, 
				hsw3000c01v3In1AudG2p1Msk, hsw3000c01v3In1AudG3p0Msk, hsw3000c01v3In1AudG3p1Msk, hsw3000c01v3In1AudG4p0Msk, hsw3000c01v3In1AudG4p1Msk, 
				hsw3000c01v3In2AudG1p0Msk, hsw3000c01v3In2AudG1p1Msk, hsw3000c01v3In2AudG2p0Msk, hsw3000c01v3In2AudG2p1Msk, hsw3000c01v3In2AudG3p0Msk, 
				hsw3000c01v3In2AudG3p1Msk, hsw3000c01v3In2AudG4p0Msk, hsw3000c01v3In2AudG4p1Msk, hsw3000c01v3SilenceLevel, hsw3000c01v3SilenceTime, 
				hsw3000c01v3OverloadLevel, hsw3000c01v3TxtLinesThrs, hsw3000c01v3In1Fail, hsw3000c01v3In1FailTrapEnable, hsw3000c01v3In2Fail, 
				hsw3000c01v3In2FailTrapEnable, hsw3000c01v3In1ExtFail, hsw3000c01v3In1ExtFailTrapEnable, hsw3000c01v3In2ExtFail, hsw3000c01v3In2ExtFailTrapEnable, 
				hsw3000c01v3BlindExtFail, hsw3000c01v3BlindExtFailTrapEnable, hsw3000c01v3EqualPid, hsw3000c01v3EqualPidTrapEnable, hsw3000c01v3SelOut1, 
				hsw3000c01v3SelOut1TrapEnable, hsw3000c01v3SelOut2, hsw3000c01v3SelOut2TrapEnable, hsw3000c01v3EqualUmid, hsw3000c01v3EqualUmidTrapEnable, 
				hsw3000c01v3Gpi3Stat, hsw3000c01v3Gpi3StatTrapEnable, hsw3000c01v3In1PhyFail, hsw3000c01v3In1PhyFailTrapEnable, hsw3000c01v3In1FmtFail, 
				hsw3000c01v3In1FmtFailTrapEnable, hsw3000c01v3In1IncFail, hsw3000c01v3In1IncFailTrapEnable, hsw3000c01v3In1GpiFail, hsw3000c01v3In1GpiFailTrapEnable, 
				hsw3000c01v3In1BlkFail, hsw3000c01v3In1BlkFailTrapEnable, hsw3000c01v3In1FrzFail, hsw3000c01v3In1FrzFailTrapEnable, hsw3000c01v3In1PatFail, 
				hsw3000c01v3In1PatFailTrapEnable, hsw3000c01v3In1CrcFail, hsw3000c01v3In1CrcFailTrapEnable, hsw3000c01v3In1SilFail, hsw3000c01v3In1SilFailTrapEnable, 
				hsw3000c01v3In1OvrFail, hsw3000c01v3In1OvrFailTrapEnable, hsw3000c01v3In1PhFail, hsw3000c01v3In1PhFailTrapEnable, hsw3000c01v3In1PreFail, 
				hsw3000c01v3In1PreFailTrapEnable, hsw3000c01v3In2PhyFail, hsw3000c01v3In2PhyFailTrapEnable, hsw3000c01v3In2FmtFail, hsw3000c01v3In2FmtFailTrapEnable, 
				hsw3000c01v3In2IncFail, hsw3000c01v3In2IncFailTrapEnable, hsw3000c01v3In2GpiFail, hsw3000c01v3In2GpiFailTrapEnable, hsw3000c01v3In2BlkFail, 
				hsw3000c01v3In2BlkFailTrapEnable, hsw3000c01v3In2FrzFail, hsw3000c01v3In2FrzFailTrapEnable, hsw3000c01v3In2PatFail, hsw3000c01v3In2PatFailTrapEnable, 
				hsw3000c01v3In2CrcFail, hsw3000c01v3In2CrcFailTrapEnable, hsw3000c01v3In2SilFail, hsw3000c01v3In2SilFailTrapEnable, hsw3000c01v3In2OvrFail, 
				hsw3000c01v3In2OvrFailTrapEnable, hsw3000c01v3In2PhFail, hsw3000c01v3In2PhFailTrapEnable, hsw3000c01v3In2PreFail, hsw3000c01v3In2PreFailTrapEnable, 
				hsw3000c01v3RefFail, hsw3000c01v3RefFailTrapEnable, hsw3000c01v3LockFail, hsw3000c01v3LockFailTrapEnable, hsw3000c01v3BliGpiFail, 
				hsw3000c01v3In1Format, hsw3000c01v3In1FormatTrapEnable, hsw3000c01v3In2Format, hsw3000c01v3In2FormatTrapEnable, hsw3000c01v3RefFormat, 
				hsw3000c01v3RefFormatTrapEnable, hsw3000c01v3In1PidPres, hsw3000c01v3In2PidPres, hsw3000c01v3In1UmidPres, hsw3000c01v3In2UmidPres, 
				hsw3000c01v3In1Grp1Pres, hsw3000c01v3In1Grp1PresTrapEnable, hsw3000c01v3In1Grp2Pres, hsw3000c01v3In1Grp2PresTrapEnable, hsw3000c01v3In1Grp3Pres, 
				hsw3000c01v3In1Grp3PresTrapEnable, hsw3000c01v3In1Grp4Pres, hsw3000c01v3In1Grp4PresTrapEnable, hsw3000c01v3In1Grp1P0Stat, hsw3000c01v3In1Grp1P0StatTrapEnable, 
				hsw3000c01v3In1Grp1P1Stat, hsw3000c01v3In1Grp1P1StatTrapEnable, hsw3000c01v3In1Grp2P0Stat, hsw3000c01v3In1Grp2P0StatTrapEnable, hsw3000c01v3In1Grp2P1Stat, 
				hsw3000c01v3In1Grp2P1StatTrapEnable, hsw3000c01v3In1Grp3P0Stat, hsw3000c01v3In1Grp3P0StatTrapEnable, hsw3000c01v3In1Grp3P1Stat, hsw3000c01v3In1Grp3P1StatTrapEnable, 
				hsw3000c01v3In1Grp4P0Stat, hsw3000c01v3In1Grp4P0StatTrapEnable, hsw3000c01v3In1Grp4P1Stat, hsw3000c01v3In1Grp4P1StatTrapEnable, hsw3000c01v3In2Grp1Pres, 
				hsw3000c01v3In2Grp1PresTrapEnable, hsw3000c01v3In2Grp2Pres, hsw3000c01v3In2Grp2PresTrapEnable, hsw3000c01v3In2Grp3Pres, hsw3000c01v3In2Grp3PresTrapEnable, 
				hsw3000c01v3In2Grp4Pres, hsw3000c01v3In2Grp4PresTrapEnable, hsw3000c01v3In2Grp1P0Stat, hsw3000c01v3In2Grp1P0StatTrapEnable, hsw3000c01v3In2Grp1P1Stat, 
				hsw3000c01v3In2Grp1P1StatTrapEnable, hsw3000c01v3In2Grp2P0Stat, hsw3000c01v3In2Grp2P0StatTrapEnable, hsw3000c01v3In2Grp2P1Stat, hsw3000c01v3In2Grp2P1StatTrapEnable, 
				hsw3000c01v3In2Grp3P0Stat, hsw3000c01v3In2Grp3P0StatTrapEnable, hsw3000c01v3In2Grp3P1Stat, hsw3000c01v3In2Grp3P1StatTrapEnable, hsw3000c01v3In2Grp4P0Stat, 
				hsw3000c01v3In2Grp4P0StatTrapEnable, hsw3000c01v3In2Grp4P1Stat, hsw3000c01v3In2Grp4P1StatTrapEnable, hsw3000c01v3In1WssStat, hsw3000c01v3In1WssStatTrapEnable, 
				hsw3000c01v3In1ViiStat, hsw3000c01v3In1ViiStatTrapEnable, hsw3000c01v3In12016Stat, hsw3000c01v3In12016StatTrapEnable, hsw3000c01v3In2WssStat, 
				hsw3000c01v3In2WssStatTrapEnable, hsw3000c01v3In2ViiStat, hsw3000c01v3In2ViiStatTrapEnable, hsw3000c01v3In22016Stat, hsw3000c01v3In22016StatTrapEnable, 
				hsw3000c01v3In1TxtLinLow, hsw3000c01v3In1TxtLinLowTrapEnable, hsw3000c01v3In1TxtLin1s, hsw3000c01v3In2TxtLinLow, hsw3000c01v3In2TxtLinLowTrapEnable, 
				hsw3000c01v3In2TxtLin1s, hsw3000c01v3SerialNo, hsw3000c01v3GpoMode, hsw3000c01v3DePer2IncIn1, hsw3000c01v3DePer2IncIn2, 
				hsw3000c01v3FrzToBckTime, hsw3000c01v3In1WssCod, hsw3000c01v3In1WssCodTrapEnable, hsw3000c01v3In1ViiAfdCod, hsw3000c01v3In1ViiAfdCodTrapEnable, 
				hsw3000c01v3In12016AfdCod, hsw3000c01v3In12016AfdCodTrapEnable, hsw3000c01v3In2WssCod, hsw3000c01v3In2WssCodTrapEnable, hsw3000c01v3In2ViiAfdCod, 
				hsw3000c01v3In2ViiAfdCodTrapEnable, hsw3000c01v3In22016Cod, hsw3000c01v3In22016CodTrapEnable }
			STATUS current
			DESCRIPTION
				"Module HSW3000C01V3 Group"
			::= { varGroups 364803 }

		-- 1.3.6.1.4.1.10106.2.3.1.371701
		eop0020c01v1ModuleGroup OBJECT-GROUP
			OBJECTS {eop0020c01v1Index, eop0020c01v1ForceAdjacent, eop0020c01v1NoSigA, eop0020c01v1NoSigATrapEnable, eop0020c01v1UnlockA, 
				eop0020c01v1UnlockATrapEnable, eop0020c01v1LFailA, eop0020c01v1LFailATrapEnable, eop0020c01v1NoSigB, eop0020c01v1NoSigBTrapEnable, 
				eop0020c01v1UnlockB, eop0020c01v1UnlockBTrapEnable, eop0020c01v1LFailB, eop0020c01v1LFailBTrapEnable, eop0020c01v1SfpId, 
				eop0020c01v1SfpSn, eop0020c01v1Temperature, eop0020c01v1RxPowerA, eop0020c01v1RxPowerB }
			STATUS current
			DESCRIPTION
				"Module EOP0020C01V1 Group"
			::= { varGroups 371701 }

		-- 1.3.6.1.4.1.10106.2.3.1.373501
		hop3147c01v1ModuleGroup OBJECT-GROUP
			OBJECTS {hop3147c01v1Index, hop3147c01v1TxtInsEna1, hop3147c01v1TxtInsEna2, hop3147c01v1Op47InsEna, hop3147c01v1TxtCleanEna1, 
				hop3147c01v1TxtCleanEna2, hop3147c01v1Op47CleanEna, hop3147c01v1LumChromN, hop3147c01v1Gpo8SigFail, hop3147c01v1Op47PckInsLin, 
				hop3147c01v1TxtInsLine1, hop3147c01v1TxtInsLine2, hop3147c01v1TxtRdLine, hop3147c01v1TxtRdEna, hop3147c01v1NoSignal, 
				hop3147c01v1NoSignalTrapEnable, hop3147c01v1Unlock, hop3147c01v1UnlockTrapEnable, hop3147c01v1EdhError, hop3147c01v1EdhErrorTrapEnable, 
				hop3147c01v1TxtFail, hop3147c01v1TxtFailTrapEnable, hop3147c01v1TxtInsFail, hop3147c01v1TxtInsFailTrapEnable, hop3147c01v1Format, 
				hop3147c01v1Gpi1, hop3147c01v1Gpi1TrapEnable, hop3147c01v1Gpi2, hop3147c01v1Gpi2TrapEnable, hop3147c01v1Gpi3, 
				hop3147c01v1Gpi3TrapEnable, hop3147c01v1Gpi4, hop3147c01v1Gpi4TrapEnable, hop3147c01v1Gpi5, hop3147c01v1Gpi5TrapEnable, 
				hop3147c01v1Gpi6, hop3147c01v1Gpi6TrapEnable, hop3147c01v1Gpi7, hop3147c01v1Gpi7TrapEnable, hop3147c01v1Gpi8, 
				hop3147c01v1Gpi8TrapEnable, hop3147c01v1Gpo1, hop3147c01v1Gpo1TrapEnable, hop3147c01v1Gpo2, hop3147c01v1Gpo2TrapEnable, 
				hop3147c01v1Gpo3, hop3147c01v1Gpo3TrapEnable, hop3147c01v1Gpo4, hop3147c01v1Gpo4TrapEnable, hop3147c01v1Gpo5, 
				hop3147c01v1Gpo5TrapEnable, hop3147c01v1Gpo6, hop3147c01v1Gpo6TrapEnable, hop3147c01v1Gpo7, hop3147c01v1Gpo7TrapEnable, 
				hop3147c01v1Gpo8, hop3147c01v1Gpo8TrapEnable, hop3147c01v1SerialNo }
			STATUS current
			DESCRIPTION
				"Module HOP3147C01V1 Group"
			::= { varGroups 373501 }

		-- 1.3.6.1.4.1.10106.2.3.1.375001
		hvp3000c01v1ModuleGroup OBJECT-GROUP
			OBJECTS {hvp3000c01v1Index, hvp3000c01v1Output1, hvp3000c01v1Output1TrapEnable, hvp3000c01v1Output2, hvp3000c01v1Output2TrapEnable, 
				hvp3000c01v1Output3, hvp3000c01v1Output3TrapEnable, hvp3000c01v1Output4, hvp3000c01v1Output4TrapEnable, hvp3000c01v1SwitchTime, 
				hvp3000c01v1HvpMode, hvp3000c01v1CasdadeMode, hvp3000c01v1SwitchMode, hvp3000c01v1InputOffset, hvp3000c01v1SyncFormat, 
				hvp3000c01v1SyncFormatTrapEnable, hvp3000c01v1Out1LckStat, hvp3000c01v1Out1LckStatTrapEnable, hvp3000c01v1Out2LckStat, hvp3000c01v1Out2LckStatTrapEnable, 
				hvp3000c01v1Out3LckStat, hvp3000c01v1Out3LckStatTrapEnable, hvp3000c01v1Out4LckStat, hvp3000c01v1Out4LckStatTrapEnable, hvp3000c01v1SerialNo }
			STATUS current
			DESCRIPTION
				"Module HVP3000C01V1 Group"
			::= { varGroups 375001 }

		-- 1.3.6.1.4.1.10106.2.3.1.376001
		tle0001c01v1ModuleGroup OBJECT-GROUP
			OBJECTS {tle0001c01v1Index, tle0001c01v1App1Ena, tle0001c01v1App2Ena, tle0001c01v1App3Ena, tle0001c01v1SerialNo }
			STATUS current
			DESCRIPTION
				"Module TLE0001C01V1 Group"
			::= { varGroups 376001 }

		-- 1.3.6.1.4.1.10106.2.3.1.378901
		hdc3000c01v1ModuleGroup OBJECT-GROUP
			OBJECTS {hdc3000c01v1Index, hdc3000c01v1ActivePreset, hdc3000c01v1LoadPreset, hdc3000c01v1SavePreset, hdc3000c01v1AnaRefFmt, 
				hdc3000c01v1AnaRefFmtTrapEnable, hdc3000c01v1GenlockMode, hdc3000c01v1EnaAud20Bit, hdc3000c01v1ModeConv, hdc3000c01v1ModeConvTrapEnable, 
				hdc3000c01v1OutAfd, hdc3000c01v1OutAfdTrapEnable, hdc3000c01v1OutCf, hdc3000c01v1OutCfTrapEnable, hdc3000c01v1InAfdExpct, 
				hdc3000c01v1InAfdExpctTrapEnable, hdc3000c01v1InCfExpct, hdc3000c01v1InCfExpctTrapEnable, hdc3000c01v1OutsdEnaS2016, hdc3000c01v1OutsdEnaVii, 
				hdc3000c01v1OutsdEnaWss, hdc3000c01v1OutsdEnaVitc, hdc3000c01v1OutsdEnaTxt, hdc3000c01v1SelAudPair0, hdc3000c01v1SelAudPair1, 
				hdc3000c01v1SelAudPair2, hdc3000c01v1SelAudPair3, hdc3000c01v1SelAudPair4, hdc3000c01v1SelAudPair5, hdc3000c01v1SelAudPair6, 
				hdc3000c01v1SelAudPair7, hdc3000c01v1VDelay, hdc3000c01v1HDelay, hdc3000c01v1VDelaySd, hdc3000c01v1HDelaySd, 
				hdc3000c01v1Grp1P0Gain, hdc3000c01v1Grp1P0Phase, hdc3000c01v1Grp1P1Gain, hdc3000c01v1Grp1P1Phase, hdc3000c01v1Grp2P0Gain, 
				hdc3000c01v1Grp2P0Phase, hdc3000c01v1Grp2P1Gain, hdc3000c01v1Grp2P1Phase, hdc3000c01v1Grp3P0Gain, hdc3000c01v1Grp3P0Phase, 
				hdc3000c01v1Grp3P1Gain, hdc3000c01v1Grp3P1Phase, hdc3000c01v1Grp4P0Gain, hdc3000c01v1Grp4P0Phase, hdc3000c01v1Grp4P1Gain, 
				hdc3000c01v1Grp4P1Phase, hdc3000c01v1InAfdDetct, hdc3000c01v1InAfdDetctTrapEnable, hdc3000c01v1InCfDetct, hdc3000c01v1InCfDetctTrapEnable, 
				hdc3000c01v1InPhyFail, hdc3000c01v1InPhyFailTrapEnable, hdc3000c01v1InFmtFail, hdc3000c01v1InFmtFailTrapEnable, hdc3000c01v1InIncFail, 
				hdc3000c01v1InIncFailTrapEnable, hdc3000c01v1InPresCrcFail, hdc3000c01v1InCrcFail, hdc3000c01v1InCrcFailTrapEnable, hdc3000c01v1InPrsS352Fail, 
				hdc3000c01v1InS352Fail, hdc3000c01v1PresS2016Fail, hdc3000c01v1ErrS2016Fail, hdc3000c01v1PresAudG1Fail, hdc3000c01v1PresAudG1FailTrapEnable, 
				hdc3000c01v1PresAudG2Fail, hdc3000c01v1PresAudG2FailTrapEnable, hdc3000c01v1PresAudG3Fail, hdc3000c01v1PresAudG3FailTrapEnable, hdc3000c01v1PresAudG4Fail, 
				hdc3000c01v1PresAudG4FailTrapEnable, hdc3000c01v1RefFail, hdc3000c01v1RefFailTrapEnable, hdc3000c01v1RefFmtFail, hdc3000c01v1RefFmtFailTrapEnable, 
				hdc3000c01v1LockFail, hdc3000c01v1LockFailTrapEnable, hdc3000c01v1AudPair0Fail, hdc3000c01v1AudPair0FailTrapEnable, hdc3000c01v1AudPair1Fail, 
				hdc3000c01v1AudPair1FailTrapEnable, hdc3000c01v1AudPair2Fail, hdc3000c01v1AudPair2FailTrapEnable, hdc3000c01v1AudPair3Fail, hdc3000c01v1AudPair3FailTrapEnable, 
				hdc3000c01v1AudPair4Fail, hdc3000c01v1AudPair4FailTrapEnable, hdc3000c01v1AudPair5Fail, hdc3000c01v1AudPair5FailTrapEnable, hdc3000c01v1AudPair6Fail, 
				hdc3000c01v1AudPair6FailTrapEnable, hdc3000c01v1AudPair7Fail, hdc3000c01v1AudPair7FailTrapEnable, hdc3000c01v1InFormat, hdc3000c01v1InFormatTrapEnable, 
				hdc3000c01v1RefFormat, hdc3000c01v1RefFormatTrapEnable, hdc3000c01v1Mute, hdc3000c01v1Black, hdc3000c01v1MuteSd, 
				hdc3000c01v1BlackSd, hdc3000c01v1Gpi1, hdc3000c01v1Gpi2, hdc3000c01v1Gpi3, hdc3000c01v1Gpi4, 
				hdc3000c01v1SerialNo, hdc3000c01v1OutsdEnaCea608 }
			STATUS current
			DESCRIPTION
				"Module HDC3000C01V1 Group"
			::= { varGroups 378901 }

		-- 1.3.6.1.4.1.10106.2.3.1.379801
		hli3000c01v1ModuleGroup OBJECT-GROUP
			OBJECTS {hli3000c01v1Index, hli3000c01v1ActivePreset, hli3000c01v1LoadPreset, hli3000c01v1SavePreset, hli3000c01v1PgmInsLogo1, 
				hli3000c01v1PgmInsLogo1TrapEnable, hli3000c01v1PgmInsLogo2, hli3000c01v1PgmInsLogo2TrapEnable, hli3000c01v1PgmInsLogo3, hli3000c01v1PgmInsLogo3TrapEnable, 
				hli3000c01v1PgmInsLogo4, hli3000c01v1PgmInsLogo4TrapEnable, hli3000c01v1PvwInsLogo1, hli3000c01v1PvwInsLogo2, hli3000c01v1PvwInsLogo3, 
				hli3000c01v1PvwInsLogo4, hli3000c01v1SelLogo1, hli3000c01v1SelLogo1TrapEnable, hli3000c01v1SelLogo2, hli3000c01v1SelLogo2TrapEnable, 
				hli3000c01v1SelLogo3, hli3000c01v1SelLogo3TrapEnable, hli3000c01v1SelLogo4, hli3000c01v1SelLogo4TrapEnable, hli3000c01v1PosHLogo1, 
				hli3000c01v1PosVLogo1, hli3000c01v1PosHLogo2, hli3000c01v1PosVLogo2, hli3000c01v1PosHLogo3, hli3000c01v1PosVLogo3, 
				hli3000c01v1PosHLogo4, hli3000c01v1PosVLogo4, hli3000c01v1InputFPresSel, hli3000c01v1NoSignal, hli3000c01v1NoSignalTrapEnable, 
				hli3000c01v1Unlock, hli3000c01v1UnlockTrapEnable, hli3000c01v1EdhError, hli3000c01v1EdhErrorTrapEnable, hli3000c01v1Format, 
				hli3000c01v1FormatTrapEnable, hli3000c01v1Gpi1, hli3000c01v1Gpi1TrapEnable, hli3000c01v1Gpi2, hli3000c01v1Gpi2TrapEnable, 
				hli3000c01v1Gpi3, hli3000c01v1Gpi3TrapEnable, hli3000c01v1Gpi4, hli3000c01v1Gpi4TrapEnable, hli3000c01v1Gpi5, 
				hli3000c01v1Gpi5TrapEnable, hli3000c01v1Gpi6, hli3000c01v1Gpi6TrapEnable, hli3000c01v1Gpi7, hli3000c01v1Gpi7TrapEnable, 
				hli3000c01v1Gpi8, hli3000c01v1Gpi8TrapEnable, hli3000c01v1LdLogo1Stat, hli3000c01v1LdLogo2Stat, hli3000c01v1LdLogo3Stat, 
				hli3000c01v1LdLogo4Stat, hli3000c01v1SerialNo }
			STATUS current
			DESCRIPTION
				"Module HLI3000C01V1 Group"
			::= { varGroups 379801 }

		-- 1.3.6.1.4.1.10106.2.3.1.379802
		hli3000c01v2ModuleGroup OBJECT-GROUP
			OBJECTS {hli3000c01v2Index, hli3000c01v2ActivePreset, hli3000c01v2ActivePresetTrapEnable, hli3000c01v2LoadPreset, hli3000c01v2SavePreset, 
				hli3000c01v2PgmInsLogo1, hli3000c01v2PgmInsLogo1TrapEnable, hli3000c01v2PgmInsLogo2, hli3000c01v2PgmInsLogo2TrapEnable, hli3000c01v2PgmInsLogo3, 
				hli3000c01v2PgmInsLogo3TrapEnable, hli3000c01v2PgmInsLogo4, hli3000c01v2PgmInsLogo4TrapEnable, hli3000c01v2PvwInsLogo1, hli3000c01v2PvwInsLogo2, 
				hli3000c01v2PvwInsLogo3, hli3000c01v2PvwInsLogo4, hli3000c01v2ClockSource, hli3000c01v2PgmInsClock, hli3000c01v2PvwInsClock, 
				hli3000c01v2ClockPosition, hli3000c01v2SelLogo1, hli3000c01v2SelLogo1TrapEnable, hli3000c01v2SelLogo2, hli3000c01v2SelLogo2TrapEnable, 
				hli3000c01v2SelLogo3, hli3000c01v2SelLogo3TrapEnable, hli3000c01v2SelLogo4, hli3000c01v2SelLogo4TrapEnable, hli3000c01v2PosHLogo1, 
				hli3000c01v2PosVLogo1, hli3000c01v2PosHLogo2, hli3000c01v2PosVLogo2, hli3000c01v2PosHLogo3, hli3000c01v2PosVLogo3, 
				hli3000c01v2PosHLogo4, hli3000c01v2PosVLogo4, hli3000c01v2EnaMovLogo1, hli3000c01v2EnaMovLogo2, hli3000c01v2EnaMovLogo3, 
				hli3000c01v2EnaMovLogo4, hli3000c01v2MovLogoSpeed, hli3000c01v2MovLogoIncX, hli3000c01v2MovLogoIncY, hli3000c01v2CrawlEnLogo1, 
				hli3000c01v2CrawlEnLogo2, hli3000c01v2CrawlEnLogo3, hli3000c01v2CrawlEnLogo4, hli3000c01v2CrwlContLogo1, hli3000c01v2CrwlContLogo2, 
				hli3000c01v2CrwlContLogo3, hli3000c01v2CrwlContLogo4, hli3000c01v2InputFPresSel, hli3000c01v2ClockFormat, hli3000c01v2ClockAmPm, 
				hli3000c01v2ClockSize, hli3000c01v2CrawlSpeed, hli3000c01v2CrawlTimeS, hli3000c01v2CrawlTimeM, hli3000c01v2CrawlTimeH, 
				hli3000c01v2NoSignal, hli3000c01v2NoSignalTrapEnable, hli3000c01v2Unlock, hli3000c01v2UnlockTrapEnable, hli3000c01v2EdhError, 
				hli3000c01v2EdhErrorTrapEnable, hli3000c01v2Format, hli3000c01v2FormatTrapEnable, hli3000c01v2Gpi1, hli3000c01v2Gpi1TrapEnable, 
				hli3000c01v2Gpi2, hli3000c01v2Gpi2TrapEnable, hli3000c01v2Gpi3, hli3000c01v2Gpi3TrapEnable, hli3000c01v2Gpi4, 
				hli3000c01v2Gpi4TrapEnable, hli3000c01v2Gpi5, hli3000c01v2Gpi5TrapEnable, hli3000c01v2Gpi6, hli3000c01v2Gpi6TrapEnable, 
				hli3000c01v2Gpi7, hli3000c01v2Gpi7TrapEnable, hli3000c01v2Gpi8, hli3000c01v2Gpi8TrapEnable, hli3000c01v2LdLogo1Stat, 
				hli3000c01v2LdLogo2Stat, hli3000c01v2LdLogo3Stat, hli3000c01v2LdLogo4Stat, hli3000c01v2SerialNo }
			STATUS current
			DESCRIPTION
				"Module HLI3000C01V2 Group"
			::= { varGroups 379802 }

		-- 1.3.6.1.4.1.10106.2.3.1.380001
		eop0010c01v1ModuleGroup OBJECT-GROUP
			OBJECTS {eop0010c01v1Index, eop0010c01v1ForceAdjacent, eop0010c01v1NoSigA, eop0010c01v1NoSigATrapEnable, eop0010c01v1UnlockA, 
				eop0010c01v1UnlockATrapEnable, eop0010c01v1LFailA, eop0010c01v1LFailATrapEnable, eop0010c01v1NoSigB, eop0010c01v1NoSigBTrapEnable, 
				eop0010c01v1UnlockB, eop0010c01v1UnlockBTrapEnable, eop0010c01v1LFailB, eop0010c01v1LFailBTrapEnable, eop0010c01v1SfpId, 
				eop0010c01v1SfpSn, eop0010c01v1Temperature, eop0010c01v1RxPowerA, eop0010c01v1RxPowerB }
			STATUS current
			DESCRIPTION
				"Module EOP0010C01V1 Group"
			::= { varGroups 380001 }

		-- 1.3.6.1.4.1.10106.2.3.1.382501
		hap3000c01v1ModuleGroup OBJECT-GROUP
			OBJECTS {hap3000c01v1Index, hap3000c01v1ActivePreset, hap3000c01v1LoadPreset, hap3000c01v1SavePreset, hap3000c01v1SynchroMode, 
				hap3000c01v1FailMode, hap3000c01v1DelayMode, hap3000c01v1HDelay, hap3000c01v1FrameDelay, hap3000c01v1VDelay, 
				hap3000c01v1Grp12Mult, hap3000c01v1Grp34Mult, hap3000c01v1Grp1P0Mode, hap3000c01v1Grp1P1Mode, hap3000c01v1Grp2P0Mode, 
				hap3000c01v1Grp2P1Mode, hap3000c01v1Grp3P0Mode, hap3000c01v1Grp3P1Mode, hap3000c01v1Grp4P0Mode, hap3000c01v1Grp4P1Mode, 
				hap3000c01v1ProcessingG1p0, hap3000c01v1ProcessingG1p1, hap3000c01v1ProcessingG2p0, hap3000c01v1ProcessingG2p1, hap3000c01v1ProcessingG3p0, 
				hap3000c01v1ProcessingG3p1, hap3000c01v1ProcessingG4p0, hap3000c01v1ProcessingG4p1, hap3000c01v1LimiterG1p0, hap3000c01v1LimiterG1p1, 
				hap3000c01v1LimiterG2p0, hap3000c01v1LimiterG2p1, hap3000c01v1LimiterG3p0, hap3000c01v1LimiterG3p1, hap3000c01v1LimiterG4p0, 
				hap3000c01v1LimiterG4p1, hap3000c01v1TransientG1p0, hap3000c01v1TransientG1p1, hap3000c01v1TransientG2p0, hap3000c01v1TransientG2p1, 
				hap3000c01v1TransientG3p0, hap3000c01v1TransientG3p1, hap3000c01v1TransientG4p0, hap3000c01v1TransientG4p1, hap3000c01v1LoudnessG1p0, 
				hap3000c01v1LoudnessG1p1, hap3000c01v1LoudnessG2p0, hap3000c01v1LoudnessG2p1, hap3000c01v1LoudnessG3p0, hap3000c01v1LoudnessG3p1, 
				hap3000c01v1LoudnessG4p0, hap3000c01v1LoudnessG4p1, hap3000c01v1LoudTarg, hap3000c01v1TruePeakMax, hap3000c01v1Grp1P0A, 
				hap3000c01v1Grp1P1A, hap3000c01v1Grp2P0A, hap3000c01v1Grp2P1A, hap3000c01v1Grp3P0A, hap3000c01v1Grp3P1A, 
				hap3000c01v1Grp4P0A, hap3000c01v1Grp4P1A, hap3000c01v1MeasPlace, hap3000c01v1SelLoudMeas, hap3000c01v1StatMeas, 
				hap3000c01v1OsdEnable, hap3000c01v1DispPeak, hap3000c01v1DispLoudness, hap3000c01v1Meter1, hap3000c01v1Meter2, 
				hap3000c01v1Meter3, hap3000c01v1Meter4, hap3000c01v1Meter5, hap3000c01v1Meter6, hap3000c01v1Meter7, 
				hap3000c01v1Meter8, hap3000c01v1DispMode, hap3000c01v1StatFlash, hap3000c01v1NoSig, hap3000c01v1NoSigTrapEnable, 
				hap3000c01v1Unlock, hap3000c01v1UnlockTrapEnable, hap3000c01v1EdhCrc, hap3000c01v1EdhCrcTrapEnable, hap3000c01v1NoRef, 
				hap3000c01v1NoRefTrapEnable, hap3000c01v1RefUnlck, hap3000c01v1RefUnlckTrapEnable, hap3000c01v1AudioFail, hap3000c01v1AudioFailTrapEnable, 
				hap3000c01v1FormatIn, hap3000c01v1FormatRef, hap3000c01v1SigDelay, hap3000c01v1SerialNo }
			STATUS current
			DESCRIPTION
				"Module HAP3000C01V1 Group"
			::= { varGroups 382501 }

		-- 1.3.6.1.4.1.10106.2.3.1.382502
		hap3000c01v2ModuleGroup OBJECT-GROUP
			OBJECTS {hap3000c01v2Index, hap3000c01v2ActivePreset, hap3000c01v2LoadPreset, hap3000c01v2SavePreset, hap3000c01v2SynchroMode, 
				hap3000c01v2FailMode, hap3000c01v2DelayMode, hap3000c01v2HDelay, hap3000c01v2FrameDelay, hap3000c01v2VDelay, 
				hap3000c01v2Grp12Mult, hap3000c01v2Grp34Mult, hap3000c01v2Grp1P0Mode, hap3000c01v2Grp1P1Mode, hap3000c01v2Grp2P0Mode, 
				hap3000c01v2Grp2P1Mode, hap3000c01v2Grp3P0Mode, hap3000c01v2Grp3P1Mode, hap3000c01v2Grp4P0Mode, hap3000c01v2Grp4P1Mode, 
				hap3000c01v2ProcessingG1p0, hap3000c01v2ProcessingG1p1, hap3000c01v2ProcessingG2p0, hap3000c01v2ProcessingG2p1, hap3000c01v2ProcessingG3p0, 
				hap3000c01v2ProcessingG3p1, hap3000c01v2ProcessingG4p0, hap3000c01v2ProcessingG4p1, hap3000c01v2LimiterG1p0, hap3000c01v2LimiterG1p1, 
				hap3000c01v2LimiterG2p0, hap3000c01v2LimiterG2p1, hap3000c01v2LimiterG3p0, hap3000c01v2LimiterG3p1, hap3000c01v2LimiterG4p0, 
				hap3000c01v2LimiterG4p1, hap3000c01v2TransientG1p0, hap3000c01v2TransientG1p1, hap3000c01v2TransientG2p0, hap3000c01v2TransientG2p1, 
				hap3000c01v2TransientG3p0, hap3000c01v2TransientG3p1, hap3000c01v2TransientG4p0, hap3000c01v2TransientG4p1, hap3000c01v2LoudnessG1p0, 
				hap3000c01v2LoudnessG1p1, hap3000c01v2LoudnessG2p0, hap3000c01v2LoudnessG2p1, hap3000c01v2LoudnessG3p0, hap3000c01v2LoudnessG3p1, 
				hap3000c01v2LoudnessG4p0, hap3000c01v2LoudnessG4p1, hap3000c01v2LoudTarg, hap3000c01v2TruePeakMax, hap3000c01v2Grp1P0A, 
				hap3000c01v2Grp1P1A, hap3000c01v2Grp2P0A, hap3000c01v2Grp2P1A, hap3000c01v2Grp3P0A, hap3000c01v2Grp3P1A, 
				hap3000c01v2Grp4P0A, hap3000c01v2Grp4P1A, hap3000c01v2MeasPlace, hap3000c01v2SelLoudMeas, hap3000c01v2StatMeas, 
				hap3000c01v2OsdEnable, hap3000c01v2DispPeak, hap3000c01v2DispLoudness, hap3000c01v2Meter1, hap3000c01v2Meter2, 
				hap3000c01v2Meter3, hap3000c01v2Meter4, hap3000c01v2Meter5, hap3000c01v2Meter6, hap3000c01v2Meter7, 
				hap3000c01v2Meter8, hap3000c01v2DispMode, hap3000c01v2StatFlash, hap3000c01v2NoSig, hap3000c01v2NoSigTrapEnable, 
				hap3000c01v2Unlock, hap3000c01v2UnlockTrapEnable, hap3000c01v2EdhCrc, hap3000c01v2EdhCrcTrapEnable, hap3000c01v2NoRef, 
				hap3000c01v2NoRefTrapEnable, hap3000c01v2RefUnlck, hap3000c01v2RefUnlckTrapEnable, hap3000c01v2AudioFail, hap3000c01v2AudioFailTrapEnable, 
				hap3000c01v2FormatIn, hap3000c01v2FormatRef, hap3000c01v2SigDelay, hap3000c01v2SerialNo }
			STATUS current
			DESCRIPTION
				"Module HAP3000C01V2 Group"
			::= { varGroups 382502 }

		-- 1.3.6.1.4.1.10106.2.3.1.386801
		psu3300c01v1ModuleGroup OBJECT-GROUP
			OBJECTS {psu3300c01v1Index, psu3300c01v1PowerOff, psu3300c01v1PowerOffTrapEnable, psu3300c01v1TempWarning, psu3300c01v1TempWarningTrapEnable, 
				psu3300c01v1TempFail, psu3300c01v1TempFailTrapEnable, psu3300c01v1ActTemp, psu3300c01v1MeanTemp, psu3300c01v1MaxTemp, 
				psu3300c01v1PonHours, psu3300c01v1TotMaxTemp, psu3300c01v1TotPonHours, psu3300c01v1TotPonTimes, psu3300c01v1SerialNo, 
				psu3300c01v1InputVolt }
			STATUS current
			DESCRIPTION
				"Module PSU3300C01V1 Group"
			::= { varGroups 386801 }

		-- 1.3.6.1.4.1.10106.2.3.1.388901
		psu3300c02v1ModuleGroup OBJECT-GROUP
			OBJECTS {psu3300c02v1Index, psu3300c02v1PowerOff, psu3300c02v1PowerOffTrapEnable, psu3300c02v1TempWarning, psu3300c02v1TempWarningTrapEnable, 
				psu3300c02v1TempFail, psu3300c02v1TempFailTrapEnable, psu3300c02v1ActTemp, psu3300c02v1MeanTemp, psu3300c02v1MaxTemp, 
				psu3300c02v1PonHours, psu3300c02v1TotMaxTemp, psu3300c02v1TotPonHours, psu3300c02v1TotPonTimes, psu3300c02v1SerialNo }
			STATUS current
			DESCRIPTION
				"Module PSU3300C02V1 Group"
			::= { varGroups 388901 }

		-- 1.3.6.1.4.1.10106.2.3.1.389201
		psu3301c01v1ModuleGroup OBJECT-GROUP
			OBJECTS {psu3301c01v1Index, psu3301c01v1PowerOff, psu3301c01v1PowerOffTrapEnable, psu3301c01v1TempWarning, psu3301c01v1TempWarningTrapEnable, 
				psu3301c01v1TempFail, psu3301c01v1TempFailTrapEnable, psu3301c01v1ActTemp, psu3301c01v1MeanTemp, psu3301c01v1MaxTemp, 
				psu3301c01v1PonHours, psu3301c01v1TotMaxTemp, psu3301c01v1TotPonHours, psu3301c01v1TotPonTimes, psu3301c01v1SerialNo, 
				psu3301c01v1InputVolt }
			STATUS current
			DESCRIPTION
				"Module PSU3301C01V1 Group"
			::= { varGroups 389201 }

		-- 1.3.6.1.4.1.10106.2.3.1.389501
		psu3301c03v1ModuleGroup OBJECT-GROUP
			OBJECTS {psu3301c03v1Index, psu3301c03v1PowerOff, psu3301c03v1PowerOffTrapEnable, psu3301c03v1TempWarning, psu3301c03v1TempWarningTrapEnable, 
				psu3301c03v1TempFail, psu3301c03v1TempFailTrapEnable, psu3301c03v1ActTemp, psu3301c03v1MeanTemp, psu3301c03v1MaxTemp, 
				psu3301c03v1PonHours, psu3301c03v1TotMaxTemp, psu3301c03v1TotPonHours, psu3301c03v1TotPonTimes, psu3301c03v1SerialNo, 
				psu3301c03v1InputVolt }
			STATUS current
			DESCRIPTION
				"Module PSU3301C03V1 Group"
			::= { varGroups 389501 }

		-- 1.3.6.1.4.1.10106.2.3.1.392001
		avd3001c02v1ModuleGroup OBJECT-GROUP
			OBJECTS {avd3001c02v1Index, avd3001c02v1ClampEnable, avd3001c02v1ClampMode, avd3001c02v1NoSigA, avd3001c02v1NoSigATrapEnable, 
				avd3001c02v1UnlockA, avd3001c02v1UnlockATrapEnable, avd3001c02v1SyncFormat, avd3001c02v1SyncFormatTrapEnable, avd3001c02v1SerialNo }
			STATUS current
			DESCRIPTION
				"Module AVD3001C02V1 Group"
			::= { varGroups 392001 }

		-- 1.3.6.1.4.1.10106.2.3.1.393601
		avd3001c01v1ModuleGroup OBJECT-GROUP
			OBJECTS {avd3001c01v1Index, avd3001c01v1ClampEnable, avd3001c01v1ClampMode, avd3001c01v1NoSigA, avd3001c01v1NoSigATrapEnable, 
				avd3001c01v1UnlockA, avd3001c01v1UnlockATrapEnable, avd3001c01v1SyncFormat, avd3001c01v1SyncFormatTrapEnable, avd3001c01v1SerialNo }
			STATUS current
			DESCRIPTION
				"Module AVD3001C01V1 Group"
			::= { varGroups 393601 }

		-- 1.3.6.1.4.1.10106.2.3.1.393701
		avd3001c03v1ModuleGroup OBJECT-GROUP
			OBJECTS {avd3001c03v1Index, avd3001c03v1NoSigA, avd3001c03v1NoSigATrapEnable, avd3001c03v1UnlockA, avd3001c03v1UnlockATrapEnable, 
				avd3001c03v1SyncFormat, avd3001c03v1SyncFormatTrapEnable, avd3001c03v1SerialNo }
			STATUS current
			DESCRIPTION
				"Module AVD3001C03V1 Group"
			::= { varGroups 393701 }

		-- 1.3.6.1.4.1.10106.2.3.1.399601
		vgp3000c01v1ModuleGroup OBJECT-GROUP
			OBJECTS {vgp3000c01v1Index, vgp3000c01v1GpioStatMode, vgp3000c01v1Gpo1SGpi1Ena, vgp3000c01v1Gpo1SGpi2Ena, vgp3000c01v1Gpo1SGpi3Ena, 
				vgp3000c01v1Gpo1SGpi4Ena, vgp3000c01v1Gpo1SGpi5Ena, vgp3000c01v1Gpo1SGpi6Ena, vgp3000c01v1Gpo1SGpi7Ena, vgp3000c01v1Gpo1SGpi8Ena, 
				vgp3000c01v1Gpo1SGpi1Mode, vgp3000c01v1Gpo1SGpi2Mode, vgp3000c01v1Gpo1SGpi3Mode, vgp3000c01v1Gpo1SGpi4Mode, vgp3000c01v1Gpo1SGpi5Mode, 
				vgp3000c01v1Gpo1SGpi6Mode, vgp3000c01v1Gpo1SGpi7Mode, vgp3000c01v1Gpo1SGpi8Mode, vgp3000c01v1Gpo1SDelay, vgp3000c01v1Gpo1SF, 
				vgp3000c01v1Gpo1RGpi1Ena, vgp3000c01v1Gpo1RGpi2Ena, vgp3000c01v1Gpo1RGpi3Ena, vgp3000c01v1Gpo1RGpi4Ena, vgp3000c01v1Gpo1RGpi5Ena, 
				vgp3000c01v1Gpo1RGpi6Ena, vgp3000c01v1Gpo1RGpi7Ena, vgp3000c01v1Gpo1RGpi8Ena, vgp3000c01v1Gpo1RGpi1Mode, vgp3000c01v1Gpo1RGpi2Mode, 
				vgp3000c01v1Gpo1RGpi3Mode, vgp3000c01v1Gpo1RGpi4Mode, vgp3000c01v1Gpo1RGpi5Mode, vgp3000c01v1Gpo1RGpi6Mode, vgp3000c01v1Gpo1RGpi7Mode, 
				vgp3000c01v1Gpo1RGpi8Mode, vgp3000c01v1Gpo1RDelay, vgp3000c01v1Gpo1RF, vgp3000c01v1Gpo2SGpi1Ena, vgp3000c01v1Gpo2SGpi2Ena, 
				vgp3000c01v1Gpo2SGpi3Ena, vgp3000c01v1Gpo2SGpi4Ena, vgp3000c01v1Gpo2SGpi5Ena, vgp3000c01v1Gpo2SGpi6Ena, vgp3000c01v1Gpo2SGpi7Ena, 
				vgp3000c01v1Gpo2SGpi8Ena, vgp3000c01v1Gpo2SGpi1Mode, vgp3000c01v1Gpo2SGpi2Mode, vgp3000c01v1Gpo2SGpi3Mode, vgp3000c01v1Gpo2SGpi4Mode, 
				vgp3000c01v1Gpo2SGpi5Mode, vgp3000c01v1Gpo2SGpi6Mode, vgp3000c01v1Gpo2SGpi7Mode, vgp3000c01v1Gpo2SGpi8Mode, vgp3000c01v1Gpo2SDelay, 
				vgp3000c01v1Gpo2SF, vgp3000c01v1Gpo2RGpi1Ena, vgp3000c01v1Gpo2RGpi2Ena, vgp3000c01v1Gpo2RGpi3Ena, vgp3000c01v1Gpo2RGpi4Ena, 
				vgp3000c01v1Gpo2RGpi5Ena, vgp3000c01v1Gpo2RGpi6Ena, vgp3000c01v1Gpo2RGpi7Ena, vgp3000c01v1Gpo2RGpi8Ena, vgp3000c01v1Gpo2RGpi1Mode, 
				vgp3000c01v1Gpo2RGpi2Mode, vgp3000c01v1Gpo2RGpi3Mode, vgp3000c01v1Gpo2RGpi4Mode, vgp3000c01v1Gpo2RGpi5Mode, vgp3000c01v1Gpo2RGpi6Mode, 
				vgp3000c01v1Gpo2RGpi7Mode, vgp3000c01v1Gpo2RGpi8Mode, vgp3000c01v1Gpo2RDelay, vgp3000c01v1Gpo2RF, vgp3000c01v1Gpo3SGpi1Ena, 
				vgp3000c01v1Gpo3SGpi2Ena, vgp3000c01v1Gpo3SGpi3Ena, vgp3000c01v1Gpo3SGpi4Ena, vgp3000c01v1Gpo3SGpi5Ena, vgp3000c01v1Gpo3SGpi6Ena, 
				vgp3000c01v1Gpo3SGpi7Ena, vgp3000c01v1Gpo3SGpi8Ena, vgp3000c01v1Gpo3SGpi1Mode, vgp3000c01v1Gpo3SGpi2Mode, vgp3000c01v1Gpo3SGpi3Mode, 
				vgp3000c01v1Gpo3SGpi4Mode, vgp3000c01v1Gpo3SGpi5Mode, vgp3000c01v1Gpo3SGpi6Mode, vgp3000c01v1Gpo3SGpi7Mode, vgp3000c01v1Gpo3SGpi8Mode, 
				vgp3000c01v1Gpo3SDelay, vgp3000c01v1Gpo3SF, vgp3000c01v1Gpo3RGpi1Ena, vgp3000c01v1Gpo3RGpi2Ena, vgp3000c01v1Gpo3RGpi3Ena, 
				vgp3000c01v1Gpo3RGpi4Ena, vgp3000c01v1Gpo3RGpi5Ena, vgp3000c01v1Gpo3RGpi6Ena, vgp3000c01v1Gpo3RGpi7Ena, vgp3000c01v1Gpo3RGpi8Ena, 
				vgp3000c01v1Gpo3RGpi1Mode, vgp3000c01v1Gpo3RGpi2Mode, vgp3000c01v1Gpo3RGpi3Mode, vgp3000c01v1Gpo3RGpi4Mode, vgp3000c01v1Gpo3RGpi5Mode, 
				vgp3000c01v1Gpo3RGpi6Mode, vgp3000c01v1Gpo3RGpi7Mode, vgp3000c01v1Gpo3RGpi8Mode, vgp3000c01v1Gpo3RDelay, vgp3000c01v1Gpo3RF, 
				vgp3000c01v1Gpo4SGpi1Ena, vgp3000c01v1Gpo4SGpi2Ena, vgp3000c01v1Gpo4SGpi3Ena, vgp3000c01v1Gpo4SGpi4Ena, vgp3000c01v1Gpo4SGpi5Ena, 
				vgp3000c01v1Gpo4SGpi6Ena, vgp3000c01v1Gpo4SGpi7Ena, vgp3000c01v1Gpo4SGpi8Ena, vgp3000c01v1Gpo4SGpi1Mode, vgp3000c01v1Gpo4SGpi2Mode, 
				vgp3000c01v1Gpo4SGpi3Mode, vgp3000c01v1Gpo4SGpi4Mode, vgp3000c01v1Gpo4SGpi5Mode, vgp3000c01v1Gpo4SGpi6Mode, vgp3000c01v1Gpo4SGpi7Mode, 
				vgp3000c01v1Gpo4SGpi8Mode, vgp3000c01v1Gpo4SDelay, vgp3000c01v1Gpo4SF, vgp3000c01v1Gpo4RGpi1Ena, vgp3000c01v1Gpo4RGpi2Ena, 
				vgp3000c01v1Gpo4RGpi3Ena, vgp3000c01v1Gpo4RGpi4Ena, vgp3000c01v1Gpo4RGpi5Ena, vgp3000c01v1Gpo4RGpi6Ena, vgp3000c01v1Gpo4RGpi7Ena, 
				vgp3000c01v1Gpo4RGpi8Ena, vgp3000c01v1Gpo4RGpi1Mode, vgp3000c01v1Gpo4RGpi2Mode, vgp3000c01v1Gpo4RGpi3Mode, vgp3000c01v1Gpo4RGpi4Mode, 
				vgp3000c01v1Gpo4RGpi5Mode, vgp3000c01v1Gpo4RGpi6Mode, vgp3000c01v1Gpo4RGpi7Mode, vgp3000c01v1Gpo4RGpi8Mode, vgp3000c01v1Gpo4RDelay, 
				vgp3000c01v1Gpo4RF, vgp3000c01v1Gpo5SGpi1Ena, vgp3000c01v1Gpo5SGpi2Ena, vgp3000c01v1Gpo5SGpi3Ena, vgp3000c01v1Gpo5SGpi4Ena, 
				vgp3000c01v1Gpo5SGpi5Ena, vgp3000c01v1Gpo5SGpi6Ena, vgp3000c01v1Gpo5SGpi7Ena, vgp3000c01v1Gpo5SGpi8Ena, vgp3000c01v1Gpo5SGpi1Mode, 
				vgp3000c01v1Gpo5SGpi2Mode, vgp3000c01v1Gpo5SGpi3Mode, vgp3000c01v1Gpo5SGpi4Mode, vgp3000c01v1Gpo5SGpi5Mode, vgp3000c01v1Gpo5SGpi6Mode, 
				vgp3000c01v1Gpo5SGpi7Mode, vgp3000c01v1Gpo5SGpi8Mode, vgp3000c01v1Gpo5SDelay, vgp3000c01v1Gpo5SF, vgp3000c01v1Gpo5RGpi1Ena, 
				vgp3000c01v1Gpo5RGpi2Ena, vgp3000c01v1Gpo5RGpi3Ena, vgp3000c01v1Gpo5RGpi4Ena, vgp3000c01v1Gpo5RGpi5Ena, vgp3000c01v1Gpo5RGpi6Ena, 
				vgp3000c01v1Gpo5RGpi7Ena, vgp3000c01v1Gpo5RGpi8Ena, vgp3000c01v1Gpo5RGpi1Mode, vgp3000c01v1Gpo5RGpi2Mode, vgp3000c01v1Gpo5RGpi3Mode, 
				vgp3000c01v1Gpo5RGpi4Mode, vgp3000c01v1Gpo5RGpi5Mode, vgp3000c01v1Gpo5RGpi6Mode, vgp3000c01v1Gpo5RGpi7Mode, vgp3000c01v1Gpo5RGpi8Mode, 
				vgp3000c01v1Gpo5RDelay, vgp3000c01v1Gpo5RF, vgp3000c01v1Gpo6SGpi1Ena, vgp3000c01v1Gpo6SGpi2Ena, vgp3000c01v1Gpo6SGpi3Ena, 
				vgp3000c01v1Gpo6SGpi4Ena, vgp3000c01v1Gpo6SGpi5Ena, vgp3000c01v1Gpo6SGpi6Ena, vgp3000c01v1Gpo6SGpi7Ena, vgp3000c01v1Gpo6SGpi8Ena, 
				vgp3000c01v1Gpo6SGpi1Mode, vgp3000c01v1Gpo6SGpi2Mode, vgp3000c01v1Gpo6SGpi3Mode, vgp3000c01v1Gpo6SGpi4Mode, vgp3000c01v1Gpo6SGpi5Mode, 
				vgp3000c01v1Gpo6SGpi6Mode, vgp3000c01v1Gpo6SGpi7Mode, vgp3000c01v1Gpo6SGpi8Mode, vgp3000c01v1Gpo6SDelay, vgp3000c01v1Gpo6SF, 
				vgp3000c01v1Gpo6RGpi1Ena, vgp3000c01v1Gpo6RGpi2Ena, vgp3000c01v1Gpo6RGpi3Ena, vgp3000c01v1Gpo6RGpi4Ena, vgp3000c01v1Gpo6RGpi5Ena, 
				vgp3000c01v1Gpo6RGpi6Ena, vgp3000c01v1Gpo6RGpi7Ena, vgp3000c01v1Gpo6RGpi8Ena, vgp3000c01v1Gpo6RGpi1Mode, vgp3000c01v1Gpo6RGpi2Mode, 
				vgp3000c01v1Gpo6RGpi3Mode, vgp3000c01v1Gpo6RGpi4Mode, vgp3000c01v1Gpo6RGpi5Mode, vgp3000c01v1Gpo6RGpi6Mode, vgp3000c01v1Gpo6RGpi7Mode, 
				vgp3000c01v1Gpo6RGpi8Mode, vgp3000c01v1Gpo6RDelay, vgp3000c01v1Gpo6RF, vgp3000c01v1Gpo7SGpi1Ena, vgp3000c01v1Gpo7SGpi2Ena, 
				vgp3000c01v1Gpo7SGpi3Ena, vgp3000c01v1Gpo7SGpi4Ena, vgp3000c01v1Gpo7SGpi5Ena, vgp3000c01v1Gpo7SGpi6Ena, vgp3000c01v1Gpo7SGpi7Ena, 
				vgp3000c01v1Gpo7SGpi8Ena, vgp3000c01v1Gpo7SGpi1Mode, vgp3000c01v1Gpo7SGpi2Mode, vgp3000c01v1Gpo7SGpi3Mode, vgp3000c01v1Gpo7SGpi4Mode, 
				vgp3000c01v1Gpo7SGpi5Mode, vgp3000c01v1Gpo7SGpi6Mode, vgp3000c01v1Gpo7SGpi7Mode, vgp3000c01v1Gpo7SGpi8Mode, vgp3000c01v1Gpo7SDelay, 
				vgp3000c01v1Gpo7SF, vgp3000c01v1Gpo7RGpi1Ena, vgp3000c01v1Gpo7RGpi2Ena, vgp3000c01v1Gpo7RGpi3Ena, vgp3000c01v1Gpo7RGpi4Ena, 
				vgp3000c01v1Gpo7RGpi5Ena, vgp3000c01v1Gpo7RGpi6Ena, vgp3000c01v1Gpo7RGpi7Ena, vgp3000c01v1Gpo7RGpi8Ena, vgp3000c01v1Gpo7RGpi1Mode, 
				vgp3000c01v1Gpo7RGpi2Mode, vgp3000c01v1Gpo7RGpi3Mode, vgp3000c01v1Gpo7RGpi4Mode, vgp3000c01v1Gpo7RGpi5Mode, vgp3000c01v1Gpo7RGpi6Mode, 
				vgp3000c01v1Gpo7RGpi7Mode, vgp3000c01v1Gpo7RGpi8Mode, vgp3000c01v1Gpo7RDelay, vgp3000c01v1Gpo7RF, vgp3000c01v1Gpo8SGpi1Ena, 
				vgp3000c01v1Gpo8SGpi2Ena, vgp3000c01v1Gpo8SGpi3Ena, vgp3000c01v1Gpo8SGpi4Ena, vgp3000c01v1Gpo8SGpi5Ena, vgp3000c01v1Gpo8SGpi6Ena, 
				vgp3000c01v1Gpo8SGpi7Ena, vgp3000c01v1Gpo8SGpi8Ena, vgp3000c01v1Gpo8SGpi1Mode, vgp3000c01v1Gpo8SGpi2Mode, vgp3000c01v1Gpo8SGpi3Mode, 
				vgp3000c01v1Gpo8SGpi4Mode, vgp3000c01v1Gpo8SGpi5Mode, vgp3000c01v1Gpo8SGpi6Mode, vgp3000c01v1Gpo8SGpi7Mode, vgp3000c01v1Gpo8SGpi8Mode, 
				vgp3000c01v1Gpo8SDelay, vgp3000c01v1Gpo8SF, vgp3000c01v1Gpo8RGpi1Ena, vgp3000c01v1Gpo8RGpi2Ena, vgp3000c01v1Gpo8RGpi3Ena, 
				vgp3000c01v1Gpo8RGpi4Ena, vgp3000c01v1Gpo8RGpi5Ena, vgp3000c01v1Gpo8RGpi6Ena, vgp3000c01v1Gpo8RGpi7Ena, vgp3000c01v1Gpo8RGpi8Ena, 
				vgp3000c01v1Gpo8RGpi1Mode, vgp3000c01v1Gpo8RGpi2Mode, vgp3000c01v1Gpo8RGpi3Mode, vgp3000c01v1Gpo8RGpi4Mode, vgp3000c01v1Gpo8RGpi5Mode, 
				vgp3000c01v1Gpo8RGpi6Mode, vgp3000c01v1Gpo8RGpi7Mode, vgp3000c01v1Gpo8RGpi8Mode, vgp3000c01v1Gpo8RDelay, vgp3000c01v1Gpo8RF, 
				vgp3000c01v1Gpi1, vgp3000c01v1Gpi1TrapEnable, vgp3000c01v1Gpi2, vgp3000c01v1Gpi2TrapEnable, vgp3000c01v1Gpi3, 
				vgp3000c01v1Gpi3TrapEnable, vgp3000c01v1Gpi4, vgp3000c01v1Gpi4TrapEnable, vgp3000c01v1Gpi5, vgp3000c01v1Gpi5TrapEnable, 
				vgp3000c01v1Gpi6, vgp3000c01v1Gpi6TrapEnable, vgp3000c01v1Gpi7, vgp3000c01v1Gpi7TrapEnable, vgp3000c01v1Gpi8, 
				vgp3000c01v1Gpi8TrapEnable, vgp3000c01v1Gpo1, vgp3000c01v1Gpo1TrapEnable, vgp3000c01v1Gpo2, vgp3000c01v1Gpo2TrapEnable, 
				vgp3000c01v1Gpo3, vgp3000c01v1Gpo3TrapEnable, vgp3000c01v1Gpo4, vgp3000c01v1Gpo4TrapEnable, vgp3000c01v1Gpo5, 
				vgp3000c01v1Gpo5TrapEnable, vgp3000c01v1Gpo6, vgp3000c01v1Gpo6TrapEnable, vgp3000c01v1Gpo7, vgp3000c01v1Gpo7TrapEnable, 
				vgp3000c01v1Gpo8, vgp3000c01v1Gpo8TrapEnable, vgp3000c01v1SerialNo }
			STATUS current
			DESCRIPTION
				"Module VGP3000C01V1 Group"
			::= { varGroups 399601 }

		-- 1.3.6.1.4.1.10106.2.3.1.403001
		ham3000c01v1ModuleGroup OBJECT-GROUP
			OBJECTS {ham3000c01v1Index, ham3000c01v1ActivePreset, ham3000c01v1LoadPreset, ham3000c01v1SynchroMode, ham3000c01v1FailMode, 
				ham3000c01v1DelayMode, ham3000c01v1HDelay, ham3000c01v1FrameDelay, ham3000c01v1VDelay, ham3000c01v1MuxAuxC1, 
				ham3000c01v1MuxAuxC2, ham3000c01v1MuxAuxC3, ham3000c01v1MuxAuxC4, ham3000c01v1FullScaleLev, ham3000c01v1OvldLevel, 
				ham3000c01v1SilenceLevel, ham3000c01v1SilenceTime, ham3000c01v1Gen1PipsTone, ham3000c01v1Gen2PipsTone, ham3000c01v1MediasGen1, 
				ham3000c01v1MediasGen2, ham3000c01v1FreqPips1, ham3000c01v1FreqPips2, ham3000c01v1LevelPips1, ham3000c01v1LevelPips2, 
				ham3000c01v1NPipsHour, ham3000c01v1NPipsHalf, ham3000c01v1ShortPerHour, ham3000c01v1ShortPerHalf, ham3000c01v1LongPerHour, 
				ham3000c01v1LongPerHalf, ham3000c01v1EmbG1p0l, ham3000c01v1EmbG1p0lMonPh, ham3000c01v1EmbG1p0lMono, ham3000c01v1EmbG1p0r, 
				ham3000c01v1EmbG1p0rMonPh, ham3000c01v1EmbG1p0rMono, ham3000c01v1EmbG1p1l, ham3000c01v1EmbG1p1lMonPh, ham3000c01v1EmbG1p1lMono, 
				ham3000c01v1EmbG1p1r, ham3000c01v1EmbG1p1rMonPh, ham3000c01v1EmbG1p1rMono, ham3000c01v1EmbG2p0l, ham3000c01v1EmbG2p0lMonPh, 
				ham3000c01v1EmbG2p0lMono, ham3000c01v1EmbG2p0r, ham3000c01v1EmbG2p0rMonPh, ham3000c01v1EmbG2p0rMono, ham3000c01v1EmbG2p1l, 
				ham3000c01v1EmbG2p1lMonPh, ham3000c01v1EmbG2p1lMono, ham3000c01v1EmbG2p1r, ham3000c01v1EmbG2p1rMonPh, ham3000c01v1EmbG2p1rMono, 
				ham3000c01v1EmbG3p0l, ham3000c01v1EmbG3p0lMonPh, ham3000c01v1EmbG3p0lMono, ham3000c01v1EmbG3p0r, ham3000c01v1EmbG3p0rMonPh, 
				ham3000c01v1EmbG3p0rMono, ham3000c01v1EmbG3p1l, ham3000c01v1EmbG3p1lMonPh, ham3000c01v1EmbG3p1lMono, ham3000c01v1EmbG3p1r, 
				ham3000c01v1EmbG3p1rMonPh, ham3000c01v1EmbG3p1rMono, ham3000c01v1EmbG4p0l, ham3000c01v1EmbG4p0lMonPh, ham3000c01v1EmbG4p0lMono, 
				ham3000c01v1EmbG4p0r, ham3000c01v1EmbG4p0rMonPh, ham3000c01v1EmbG4p0rMono, ham3000c01v1EmbG4p1l, ham3000c01v1EmbG4p1lMonPh, 
				ham3000c01v1EmbG4p1lMono, ham3000c01v1EmbG4p1r, ham3000c01v1EmbG4p1rMonPh, ham3000c01v1EmbG4p1rMono, ham3000c01v1AesOut1L, 
				ham3000c01v1AesOut1lMonPh, ham3000c01v1AesOut1lMono, ham3000c01v1AesOut1R, ham3000c01v1AesOut1rMonPh, ham3000c01v1AesOut1rMono, 
				ham3000c01v1AesOut2L, ham3000c01v1AesOut2lMonPh, ham3000c01v1AesOut2lMono, ham3000c01v1AesOut2R, ham3000c01v1AesOut2rMonPh, 
				ham3000c01v1AesOut2rMono, ham3000c01v1GanG1p0l, ham3000c01v1PhaseG1p0l, ham3000c01v1GanG1p0r, ham3000c01v1PhaseG1p0r, 
				ham3000c01v1GanG1p1l, ham3000c01v1PhaseG1p1l, ham3000c01v1GanG1p1r, ham3000c01v1PhaseG1p1r, ham3000c01v1GanG2p0l, 
				ham3000c01v1PhaseG2p0l, ham3000c01v1GanG2p0r, ham3000c01v1PhaseG2p0r, ham3000c01v1GanG2p1l, ham3000c01v1PhaseG2p1l, 
				ham3000c01v1GanG2p1r, ham3000c01v1PhaseG2p1r, ham3000c01v1GanG3p0l, ham3000c01v1PhaseG3p0l, ham3000c01v1GanG3p0r, 
				ham3000c01v1PhaseG3p0r, ham3000c01v1GanG3p1l, ham3000c01v1PhaseG3p1l, ham3000c01v1GanG3p1r, ham3000c01v1PhaseG3p1r, 
				ham3000c01v1GanG4p0l, ham3000c01v1PhaseG4p0l, ham3000c01v1GanG4p0r, ham3000c01v1PhaseG4p0r, ham3000c01v1GanG4p1l, 
				ham3000c01v1PhaseG4p1l, ham3000c01v1GanG4p1r, ham3000c01v1PhaseG4p1r, ham3000c01v1GanAes1l, ham3000c01v1PhaseAes1l, 
				ham3000c01v1GanAes1r, ham3000c01v1PhaseAes1r, ham3000c01v1GanAes2l, ham3000c01v1PhaseAes2l, ham3000c01v1GanAes2r, 
				ham3000c01v1PhaseAes2r, ham3000c01v1DelayG1p0l, ham3000c01v1DelayG1p0r, ham3000c01v1DelayG1p1l, ham3000c01v1DelayG1p1r, 
				ham3000c01v1DelayG2p0l, ham3000c01v1DelayG2p0r, ham3000c01v1DelayG2p1l, ham3000c01v1DelayG2p1r, ham3000c01v1DelayG3p0l, 
				ham3000c01v1DelayG3p0r, ham3000c01v1DelayG3p1l, ham3000c01v1DelayG3p1r, ham3000c01v1DelayG4p0l, ham3000c01v1DelayG4p0r, 
				ham3000c01v1DelayG4p1l, ham3000c01v1DelayG4p1r, ham3000c01v1DelayAes1l, ham3000c01v1DelayAes1r, ham3000c01v1DelayAes2l, 
				ham3000c01v1DelayAes2r, ham3000c01v1StatFlash, ham3000c01v1NoSignalMain, ham3000c01v1NoSignalMainTrapEnable, ham3000c01v1UnlockMain, 
				ham3000c01v1UnlockMainTrapEnable, ham3000c01v1EdhErrorMain, ham3000c01v1EdhErrorMainTrapEnable, ham3000c01v1NoSignalAux, ham3000c01v1UnlockAux, 
				ham3000c01v1EdhErrorAux, ham3000c01v1RefAbsent, ham3000c01v1RefAbsentTrapEnable, ham3000c01v1RefUnlock, ham3000c01v1RefUnlockTrapEnable, 
				ham3000c01v1FormatMainIn, ham3000c01v1FormatAuxIn, ham3000c01v1FormatRef, ham3000c01v1FormatMainTx, ham3000c01v1SigDelay, 
				ham3000c01v1Gr1MainPres, ham3000c01v1Gr1MainPresTrapEnable, ham3000c01v1Gr2MainPres, ham3000c01v1Gr2MainPresTrapEnable, ham3000c01v1Gr3MainPres, 
				ham3000c01v1Gr3MainPresTrapEnable, ham3000c01v1Gr4MainPres, ham3000c01v1Gr4MainPresTrapEnable, ham3000c01v1Gr1AuxPres, ham3000c01v1Gr2AuxPres, 
				ham3000c01v1Gr3AuxPres, ham3000c01v1Gr4AuxPres, ham3000c01v1Aes1Ok, ham3000c01v1Aes1Frq, ham3000c01v1Aes2Ok, 
				ham3000c01v1Aes2Frq, ham3000c01v1AudStatMain, ham3000c01v1AudStatMainTrapEnable, ham3000c01v1AudStatAux, ham3000c01v1AudStatAuxTrapEnable, 
				ham3000c01v1AudStatAes1, ham3000c01v1AudStatAes1TrapEnable, ham3000c01v1AudStatAes2, ham3000c01v1AudStatAes2TrapEnable, ham3000c01v1OvldPgmOut, 
				ham3000c01v1OvldPgmOutTrapEnable, ham3000c01v1OvldAes1Out, ham3000c01v1OvldAes1OutTrapEnable, ham3000c01v1OvldAes2Out, ham3000c01v1OvldAes2OutTrapEnable, 
				ham3000c01v1SilPgmOut, ham3000c01v1SilPgmOutTrapEnable, ham3000c01v1SilAes1Out, ham3000c01v1SilAes1OutTrapEnable, ham3000c01v1SilAes2Out, 
				ham3000c01v1SilAes2OutTrapEnable, ham3000c01v1SerialNo, ham3000c01v1SavePreset, ham3000c01v1VidAuxSel }
			STATUS current
			DESCRIPTION
				"Module HAM3000C01V1 Group"
			::= { varGroups 403001 }

		-- 1.3.6.1.4.1.10106.2.3.1.404701
		agw3000c01v1ModuleGroup OBJECT-GROUP
			OBJECTS {agw3000c01v1Index, agw3000c01v1Mode, agw3000c01v1ModeTrapEnable, agw3000c01v1DvbTMode, agw3000c01v1DvbTModeTrapEnable, 
				agw3000c01v1NullPckRtp, agw3000c01v1NarrowPllBw, agw3000c01v1Buzzer, agw3000c01v1GpioMode, agw3000c01v1InputStChange, 
				agw3000c01v1InputChange, agw3000c01v1EnaAsi1, agw3000c01v1EnaAsi2, agw3000c01v1EnaIp1, agw3000c01v1EnaIp2, 
				agw3000c01v1AsiOut1In, agw3000c01v1AsiOut1InTrapEnable, agw3000c01v1AsiOut2In, agw3000c01v1AsiOut2InTrapEnable, agw3000c01v1IpOut1In, 
				agw3000c01v1IpOut1InTrapEnable, agw3000c01v1IpOut2In, agw3000c01v1IpOut2InTrapEnable, agw3000c01v1PingEnable1, agw3000c01v1PingEnable2, 
				agw3000c01v1IpLinkFailEn, agw3000c01v1IpDestFailEn, agw3000c01v1MaxTimeOut, agw3000c01v1StatReset, agw3000c01v1StatSel, 
				agw3000c01v1StatMode, agw3000c01v1IgmpVersion, agw3000c01v1EthMode, agw3000c01v1PckDelAsiIn1, agw3000c01v1PckDelAsiIn2, 
				agw3000c01v1PckDelIpIn1, agw3000c01v1PckDelIpIn2, agw3000c01v1AsiIn1Prior0, agw3000c01v1AsiIn2Prior0, agw3000c01v1IpIn1Prior0, 
				agw3000c01v1IpIn2Prior0, agw3000c01v1AsiIn1Prior1, agw3000c01v1AsiIn2Prior1, agw3000c01v1IpIn1Prior1, agw3000c01v1IpIn2Prior1, 
				agw3000c01v1AsiIn1Prior2, agw3000c01v1AsiIn2Prior2, agw3000c01v1IpIn1Prior2, agw3000c01v1IpIn2Prior2, agw3000c01v1AsiIn1Prior3, 
				agw3000c01v1AsiIn2Prior3, agw3000c01v1IpIn1Prior3, agw3000c01v1IpIn2Prior3, agw3000c01v1ActivePreset, agw3000c01v1LoadPreset, 
				agw3000c01v1SavePreset, agw3000c01v1Str1UipDAdd3, agw3000c01v1Str1UipDAdd2, agw3000c01v1Str1UipDAdd1, agw3000c01v1Str1UipDAdd0, 
				agw3000c01v1Str1MipDAdd3, agw3000c01v1Str1MipDAdd2, agw3000c01v1Str1MipDAdd1, agw3000c01v1Str1MipDAdd0, agw3000c01v1Str1DPort, 
				agw3000c01v1Str1FecEna, agw3000c01v1Str1MulticEna, agw3000c01v1VlanRx1Enable, agw3000c01v1VlanRx1Id, agw3000c01v1Str2UipDAdd3, 
				agw3000c01v1Str2UipDAdd2, agw3000c01v1Str2UipDAdd1, agw3000c01v1Str2UipDAdd0, agw3000c01v1Str2MipDAdd3, agw3000c01v1Str2MipDAdd2, 
				agw3000c01v1Str2MipDAdd1, agw3000c01v1Str2MipDAdd0, agw3000c01v1Str2DPort, agw3000c01v1Str2FecEna, agw3000c01v1Str2MulticEna, 
				agw3000c01v1VlanRx2Enable, agw3000c01v1VlanRx2Id, agw3000c01v1LocalIpAdd3, agw3000c01v1LocalIpAdd2, agw3000c01v1LocalIpAdd1, 
				agw3000c01v1LocalIpAdd0, agw3000c01v1LocalIpMask3, agw3000c01v1LocalIpMask2, agw3000c01v1LocalIpMask1, agw3000c01v1LocalIpMask0, 
				agw3000c01v1LocalIpGway3, agw3000c01v1LocalIpGway2, agw3000c01v1LocalIpGway1, agw3000c01v1LocalIpGway0, agw3000c01v1Tx1UniEna, 
				agw3000c01v1Tx1MultiEna, agw3000c01v1Tx1UipAdd3, agw3000c01v1Tx1UipAdd2, agw3000c01v1Tx1UipAdd1, agw3000c01v1Tx1UipAdd0, 
				agw3000c01v1Tx1MipAdd3, agw3000c01v1Tx1MipAdd2, agw3000c01v1Tx1MipAdd1, agw3000c01v1Tx1MipAdd0, agw3000c01v1Tx1SPort, 
				agw3000c01v1Tx1DPort, agw3000c01v1VlanTxEnable1, agw3000c01v1VlanTxPrior1, agw3000c01v1VlanTxId1, agw3000c01v1Tx1LParam, 
				agw3000c01v1Tx1FecMode, agw3000c01v1Tx1DParam, agw3000c01v1Tx1TspkInIppk, agw3000c01v1Tx1RowDelay, agw3000c01v1Tx1ColDelay, 
				agw3000c01v1LowCost1, agw3000c01v1HighReliab1, agw3000c01v1HighThroughp1, agw3000c01v1LowDelay1, agw3000c01v1Precedence1, 
				agw3000c01v1Ttl1, agw3000c01v1Str1IgmFAdd3, agw3000c01v1Str1IgmFAdd2, agw3000c01v1Str1IgmFAdd1, agw3000c01v1Str1IgmFAdd0, 
				agw3000c01v1Str2IgmFAdd3, agw3000c01v1Str2IgmFAdd2, agw3000c01v1Str2IgmFAdd1, agw3000c01v1Str2IgmFAdd0, agw3000c01v1LocalIp2Add3, 
				agw3000c01v1LocalIp2Add2, agw3000c01v1LocalIp2Add1, agw3000c01v1LocalIp2Add0, agw3000c01v1LocalIp2Msk3, agw3000c01v1LocalIp2Msk2, 
				agw3000c01v1LocalIp2Msk1, agw3000c01v1LocalIp2Msk0, agw3000c01v1LocalIp2Gwy3, agw3000c01v1LocalIp2Gwy2, agw3000c01v1LocalIp2Gwy1, 
				agw3000c01v1LocalIp2Gwy0, agw3000c01v1Tx2UniEna, agw3000c01v1Tx2MultiEna, agw3000c01v1Tx2UipAdd3, agw3000c01v1Tx2UipAdd2, 
				agw3000c01v1Tx2UipAdd1, agw3000c01v1Tx2UipAdd0, agw3000c01v1Tx2MipAdd3, agw3000c01v1Tx2MipAdd2, agw3000c01v1Tx2MipAdd1, 
				agw3000c01v1Tx2MipAdd0, agw3000c01v1Tx2SPort, agw3000c01v1Tx2DPort, agw3000c01v1VlanTxEnable2, agw3000c01v1VlanTxPrior2, 
				agw3000c01v1VlanTxId2, agw3000c01v1Tx2LParam, agw3000c01v1Tx2FecMode, agw3000c01v1Tx2DParam, agw3000c01v1Tx2TspkInIppk, 
				agw3000c01v1Tx2RowDelay, agw3000c01v1Tx2ColDelay, agw3000c01v1LowCost2, agw3000c01v1HighReliab2, agw3000c01v1HighThroughp2, 
				agw3000c01v1LowDelay2, agw3000c01v1Precedence2, agw3000c01v1Ttl2, agw3000c01v1Test0, agw3000c01v1Test1, 
				agw3000c01v1Test2, agw3000c01v1Test3, agw3000c01v1Test4, agw3000c01v1Test5, agw3000c01v1AsiOut1Fail, 
				agw3000c01v1AsiOut2Fail, agw3000c01v1IpOut1Fail, agw3000c01v1IpOut2Fail, agw3000c01v1AsiIn1Fail, agw3000c01v1AsiIn1FailTrapEnable, 
				agw3000c01v1ExAsiIn1Fail, agw3000c01v1ExAsiIn1FailTrapEnable, agw3000c01v1AsiIn2Fail, agw3000c01v1AsiIn2FailTrapEnable, agw3000c01v1ExAsiIn2Fail, 
				agw3000c01v1ExAsiIn2FailTrapEnable, agw3000c01v1IpIn1Fail, agw3000c01v1IpIn1FailTrapEnable, agw3000c01v1ExIpIn1Fail, agw3000c01v1ExIpIn1FailTrapEnable, 
				agw3000c01v1IpIn2Fail, agw3000c01v1IpIn2FailTrapEnable, agw3000c01v1ExIpIn2Fail, agw3000c01v1ExIpIn2FailTrapEnable, agw3000c01v1DestAvailable1, 
				agw3000c01v1DestAvailable2, agw3000c01v1BlindModStat1, agw3000c01v1BlindModStat2, agw3000c01v1AsiIn1Delay, agw3000c01v1AsiIn2Delay, 
				agw3000c01v1IpIn1Delay, agw3000c01v1IpIn2Delay, agw3000c01v1IpRxAddress3, agw3000c01v1IpRxAddress2, agw3000c01v1IpRxAddress1, 
				agw3000c01v1IpRxAddress0, agw3000c01v1IpRxPort, agw3000c01v1LParam, agw3000c01v1FecMode, agw3000c01v1PacketSize, 
				agw3000c01v1DParam, agw3000c01v1TsPckInIpPck, agw3000c01v1PacketRate, agw3000c01v1TimeSinceReset, agw3000c01v1LostIpPck, 
				agw3000c01v1RecoveredIpPck, agw3000c01v1OutOrdIpPck, agw3000c01v1FecRate, agw3000c01v1Link, agw3000c01v1BufferStatus, 
				agw3000c01v1PingStatus1, agw3000c01v1PingStatus2, agw3000c01v1SerialNo, agw3000c01v1SpeedForce, agw3000c01v1BadCrcPck, 
				agw3000c01v1MaxDelayTxIp, agw3000c01v1InpFailMode }
			STATUS current
			DESCRIPTION
				"Module AGW3000C01V1 Group"
			::= { varGroups 404701 }

		-- 1.3.6.1.4.1.10106.2.3.1.404702
		agw3000c01v2ModuleGroup OBJECT-GROUP
			OBJECTS {agw3000c01v2Index, agw3000c01v2Mode, agw3000c01v2ModeTrapEnable, agw3000c01v2DvbTMode, agw3000c01v2DvbTModeTrapEnable, 
				agw3000c01v2NullPckRtp, agw3000c01v2NarrowPllBw, agw3000c01v2Buzzer, agw3000c01v2GpioMode, agw3000c01v2InputStChange, 
				agw3000c01v2InputChange, agw3000c01v2EnaAsi1, agw3000c01v2EnaAsi2, agw3000c01v2EnaIp1, agw3000c01v2EnaIp2, 
				agw3000c01v2AsiOut1In, agw3000c01v2AsiOut1InTrapEnable, agw3000c01v2AsiOut2In, agw3000c01v2AsiOut2InTrapEnable, agw3000c01v2IpOut1In, 
				agw3000c01v2IpOut1InTrapEnable, agw3000c01v2IpOut2In, agw3000c01v2IpOut2InTrapEnable, agw3000c01v2PingEnable1, agw3000c01v2PingEnable2, 
				agw3000c01v2IpLinkFailEn, agw3000c01v2IpDestFailEn, agw3000c01v2MaxTimeOut, agw3000c01v2StatReset, agw3000c01v2StatSel, 
				agw3000c01v2StatMode, agw3000c01v2IgmpVersion, agw3000c01v2EthMode, agw3000c01v2SpeedForce, agw3000c01v2PckDelAsiIn1, 
				agw3000c01v2PckDelAsiIn2, agw3000c01v2PckDelIpIn1, agw3000c01v2PckDelIpIn2, agw3000c01v2AsiIn1Prior0, agw3000c01v2AsiIn2Prior0, 
				agw3000c01v2IpIn1Prior0, agw3000c01v2IpIn2Prior0, agw3000c01v2AsiIn1Prior1, agw3000c01v2AsiIn2Prior1, agw3000c01v2IpIn1Prior1, 
				agw3000c01v2IpIn2Prior1, agw3000c01v2AsiIn1Prior2, agw3000c01v2AsiIn2Prior2, agw3000c01v2IpIn1Prior2, agw3000c01v2IpIn2Prior2, 
				agw3000c01v2AsiIn1Prior3, agw3000c01v2AsiIn2Prior3, agw3000c01v2IpIn1Prior3, agw3000c01v2IpIn2Prior3, agw3000c01v2ActivePreset, 
				agw3000c01v2LoadPreset, agw3000c01v2SavePreset, agw3000c01v2Str1UipDAdd3, agw3000c01v2Str1UipDAdd2, agw3000c01v2Str1UipDAdd1, 
				agw3000c01v2Str1UipDAdd0, agw3000c01v2Str1MipDAdd3, agw3000c01v2Str1MipDAdd2, agw3000c01v2Str1MipDAdd1, agw3000c01v2Str1MipDAdd0, 
				agw3000c01v2Str1DPort, agw3000c01v2Str1FecEna, agw3000c01v2Str1MulticEna, agw3000c01v2VlanRx1Enable, agw3000c01v2VlanRx1Id, 
				agw3000c01v2Str2UipDAdd3, agw3000c01v2Str2UipDAdd2, agw3000c01v2Str2UipDAdd1, agw3000c01v2Str2UipDAdd0, agw3000c01v2Str2MipDAdd3, 
				agw3000c01v2Str2MipDAdd2, agw3000c01v2Str2MipDAdd1, agw3000c01v2Str2MipDAdd0, agw3000c01v2Str2DPort, agw3000c01v2Str2FecEna, 
				agw3000c01v2Str2MulticEna, agw3000c01v2VlanRx2Enable, agw3000c01v2VlanRx2Id, agw3000c01v2LocalIpAdd3, agw3000c01v2LocalIpAdd2, 
				agw3000c01v2LocalIpAdd1, agw3000c01v2LocalIpAdd0, agw3000c01v2LocalIpMask3, agw3000c01v2LocalIpMask2, agw3000c01v2LocalIpMask1, 
				agw3000c01v2LocalIpMask0, agw3000c01v2LocalIpGway3, agw3000c01v2LocalIpGway2, agw3000c01v2LocalIpGway1, agw3000c01v2LocalIpGway0, 
				agw3000c01v2Tx1UniEna, agw3000c01v2Tx1MultiEna, agw3000c01v2Tx1UipAdd3, agw3000c01v2Tx1UipAdd2, agw3000c01v2Tx1UipAdd1, 
				agw3000c01v2Tx1UipAdd0, agw3000c01v2Tx1MipAdd3, agw3000c01v2Tx1MipAdd2, agw3000c01v2Tx1MipAdd1, agw3000c01v2Tx1MipAdd0, 
				agw3000c01v2Tx1SPort, agw3000c01v2Tx1DPort, agw3000c01v2VlanTxEnable1, agw3000c01v2VlanTxPrior1, agw3000c01v2VlanTxId1, 
				agw3000c01v2Tx1LParam, agw3000c01v2Tx1FecMode, agw3000c01v2Tx1DParam, agw3000c01v2Tx1TspkInIppk, agw3000c01v2Tx1RowDelay, 
				agw3000c01v2Tx1ColDelay, agw3000c01v2LowCost1, agw3000c01v2HighReliab1, agw3000c01v2HighThroughp1, agw3000c01v2LowDelay1, 
				agw3000c01v2Precedence1, agw3000c01v2Ttl1, agw3000c01v2Str1IgmFAdd3, agw3000c01v2Str1IgmFAdd2, agw3000c01v2Str1IgmFAdd1, 
				agw3000c01v2Str1IgmFAdd0, agw3000c01v2Str2IgmFAdd3, agw3000c01v2Str2IgmFAdd2, agw3000c01v2Str2IgmFAdd1, agw3000c01v2Str2IgmFAdd0, 
				agw3000c01v2LocalIp2Add3, agw3000c01v2LocalIp2Add2, agw3000c01v2LocalIp2Add1, agw3000c01v2LocalIp2Add0, agw3000c01v2LocalIp2Msk3, 
				agw3000c01v2LocalIp2Msk2, agw3000c01v2LocalIp2Msk1, agw3000c01v2LocalIp2Msk0, agw3000c01v2LocalIp2Gwy3, agw3000c01v2LocalIp2Gwy2, 
				agw3000c01v2LocalIp2Gwy1, agw3000c01v2LocalIp2Gwy0, agw3000c01v2Tx2UniEna, agw3000c01v2Tx2MultiEna, agw3000c01v2Tx2UipAdd3, 
				agw3000c01v2Tx2UipAdd2, agw3000c01v2Tx2UipAdd1, agw3000c01v2Tx2UipAdd0, agw3000c01v2Tx2MipAdd3, agw3000c01v2Tx2MipAdd2, 
				agw3000c01v2Tx2MipAdd1, agw3000c01v2Tx2MipAdd0, agw3000c01v2Tx2SPort, agw3000c01v2Tx2DPort, agw3000c01v2VlanTxEnable2, 
				agw3000c01v2VlanTxPrior2, agw3000c01v2VlanTxId2, agw3000c01v2Tx2LParam, agw3000c01v2Tx2FecMode, agw3000c01v2Tx2DParam, 
				agw3000c01v2Tx2TspkInIppk, agw3000c01v2Tx2RowDelay, agw3000c01v2Tx2ColDelay, agw3000c01v2LowCost2, agw3000c01v2HighReliab2, 
				agw3000c01v2HighThroughp2, agw3000c01v2LowDelay2, agw3000c01v2Precedence2, agw3000c01v2Ttl2, agw3000c01v2Test0, 
				agw3000c01v2Test1, agw3000c01v2Test2, agw3000c01v2Test3, agw3000c01v2Test4, agw3000c01v2Test5, 
				agw3000c01v2AsiOut1Fail, agw3000c01v2AsiOut2Fail, agw3000c01v2IpOut1Fail, agw3000c01v2IpOut2Fail, agw3000c01v2AsiIn1Fail, 
				agw3000c01v2AsiIn1FailTrapEnable, agw3000c01v2ExAsiIn1Fail, agw3000c01v2ExAsiIn1FailTrapEnable, agw3000c01v2AsiIn2Fail, agw3000c01v2AsiIn2FailTrapEnable, 
				agw3000c01v2ExAsiIn2Fail, agw3000c01v2ExAsiIn2FailTrapEnable, agw3000c01v2IpIn1Fail, agw3000c01v2IpIn1FailTrapEnable, agw3000c01v2ExIpIn1Fail, 
				agw3000c01v2ExIpIn1FailTrapEnable, agw3000c01v2IpIn2Fail, agw3000c01v2IpIn2FailTrapEnable, agw3000c01v2ExIpIn2Fail, agw3000c01v2ExIpIn2FailTrapEnable, 
				agw3000c01v2DestAvailable1, agw3000c01v2DestAvailable2, agw3000c01v2BlindModStat1, agw3000c01v2BlindModStat2, agw3000c01v2AsiIn1Delay, 
				agw3000c01v2AsiIn2Delay, agw3000c01v2IpIn1Delay, agw3000c01v2IpIn2Delay, agw3000c01v2IpRxAddress3, agw3000c01v2IpRxAddress2, 
				agw3000c01v2IpRxAddress1, agw3000c01v2IpRxAddress0, agw3000c01v2IpRxPort, agw3000c01v2LParam, agw3000c01v2FecMode, 
				agw3000c01v2PacketSize, agw3000c01v2DParam, agw3000c01v2TsPckInIpPck, agw3000c01v2PacketRate, agw3000c01v2TimeSinceReset, 
				agw3000c01v2LostIpPck, agw3000c01v2RecoveredIpPck, agw3000c01v2BadCrcPck, agw3000c01v2OutOrdIpPck, agw3000c01v2FecRate, 
				agw3000c01v2Link, agw3000c01v2BufferStatus, agw3000c01v2PingStatus1, agw3000c01v2PingStatus2, agw3000c01v2SerialNo, 
				agw3000c01v2MaxDelayTxIp, agw3000c01v2InpFailMode }
			STATUS current
			DESCRIPTION
				"Module AGW3000C01V2 Group"
			::= { varGroups 404702 }

		-- 1.3.6.1.4.1.10106.2.3.1.407601
		ham3000c02v1ModuleGroup OBJECT-GROUP
			OBJECTS {ham3000c02v1Index, ham3000c02v1ActivePreset, ham3000c02v1LoadPreset, ham3000c02v1SynchroMode, ham3000c02v1FailMode, 
				ham3000c02v1DelayMode, ham3000c02v1HDelay, ham3000c02v1FrameDelay, ham3000c02v1VDelay, ham3000c02v1MuxAuxC1, 
				ham3000c02v1MuxAuxC2, ham3000c02v1MuxAuxC3, ham3000c02v1MuxAuxC4, ham3000c02v1FullScaleLev, ham3000c02v1OvldLevel, 
				ham3000c02v1SilenceLevel, ham3000c02v1SilenceTime, ham3000c02v1Gen1PipsTone, ham3000c02v1Gen2PipsTone, ham3000c02v1MediasGen1, 
				ham3000c02v1MediasGen2, ham3000c02v1FreqPips1, ham3000c02v1FreqPips2, ham3000c02v1LevelPips1, ham3000c02v1LevelPips2, 
				ham3000c02v1NPipsHour, ham3000c02v1NPipsHalf, ham3000c02v1ShortPerHour, ham3000c02v1ShortPerHalf, ham3000c02v1LongPerHour, 
				ham3000c02v1LongPerHalf, ham3000c02v1EmbG1p0l, ham3000c02v1EmbG1p0lMonPh, ham3000c02v1EmbG1p0lMono, ham3000c02v1EmbG1p0r, 
				ham3000c02v1EmbG1p0rMonPh, ham3000c02v1EmbG1p0rMono, ham3000c02v1EmbG1p1l, ham3000c02v1EmbG1p1lMonPh, ham3000c02v1EmbG1p1lMono, 
				ham3000c02v1EmbG1p1r, ham3000c02v1EmbG1p1rMonPh, ham3000c02v1EmbG1p1rMono, ham3000c02v1EmbG2p0l, ham3000c02v1EmbG2p0lMonPh, 
				ham3000c02v1EmbG2p0lMono, ham3000c02v1EmbG2p0r, ham3000c02v1EmbG2p0rMonPh, ham3000c02v1EmbG2p0rMono, ham3000c02v1EmbG2p1l, 
				ham3000c02v1EmbG2p1lMonPh, ham3000c02v1EmbG2p1lMono, ham3000c02v1EmbG2p1r, ham3000c02v1EmbG2p1rMonPh, ham3000c02v1EmbG2p1rMono, 
				ham3000c02v1EmbG3p0l, ham3000c02v1EmbG3p0lMonPh, ham3000c02v1EmbG3p0lMono, ham3000c02v1EmbG3p0r, ham3000c02v1EmbG3p0rMonPh, 
				ham3000c02v1EmbG3p0rMono, ham3000c02v1EmbG3p1l, ham3000c02v1EmbG3p1lMonPh, ham3000c02v1EmbG3p1lMono, ham3000c02v1EmbG3p1r, 
				ham3000c02v1EmbG3p1rMonPh, ham3000c02v1EmbG3p1rMono, ham3000c02v1EmbG4p0l, ham3000c02v1EmbG4p0lMonPh, ham3000c02v1EmbG4p0lMono, 
				ham3000c02v1EmbG4p0r, ham3000c02v1EmbG4p0rMonPh, ham3000c02v1EmbG4p0rMono, ham3000c02v1EmbG4p1l, ham3000c02v1EmbG4p1lMonPh, 
				ham3000c02v1EmbG4p1lMono, ham3000c02v1EmbG4p1r, ham3000c02v1EmbG4p1rMonPh, ham3000c02v1EmbG4p1rMono, ham3000c02v1AesOut1L, 
				ham3000c02v1AesOut1lMonPh, ham3000c02v1AesOut1lMono, ham3000c02v1AesOut1R, ham3000c02v1AesOut1rMonPh, ham3000c02v1AesOut1rMono, 
				ham3000c02v1AesOut2L, ham3000c02v1AesOut2lMonPh, ham3000c02v1AesOut2lMono, ham3000c02v1AesOut2R, ham3000c02v1AesOut2rMonPh, 
				ham3000c02v1AesOut2rMono, ham3000c02v1GanG1p0l, ham3000c02v1PhaseG1p0l, ham3000c02v1GanG1p0r, ham3000c02v1PhaseG1p0r, 
				ham3000c02v1GanG1p1l, ham3000c02v1PhaseG1p1l, ham3000c02v1GanG1p1r, ham3000c02v1PhaseG1p1r, ham3000c02v1GanG2p0l, 
				ham3000c02v1PhaseG2p0l, ham3000c02v1GanG2p0r, ham3000c02v1PhaseG2p0r, ham3000c02v1GanG2p1l, ham3000c02v1PhaseG2p1l, 
				ham3000c02v1GanG2p1r, ham3000c02v1PhaseG2p1r, ham3000c02v1GanG3p0l, ham3000c02v1PhaseG3p0l, ham3000c02v1GanG3p0r, 
				ham3000c02v1PhaseG3p0r, ham3000c02v1GanG3p1l, ham3000c02v1PhaseG3p1l, ham3000c02v1GanG3p1r, ham3000c02v1PhaseG3p1r, 
				ham3000c02v1GanG4p0l, ham3000c02v1PhaseG4p0l, ham3000c02v1GanG4p0r, ham3000c02v1PhaseG4p0r, ham3000c02v1GanG4p1l, 
				ham3000c02v1PhaseG4p1l, ham3000c02v1GanG4p1r, ham3000c02v1PhaseG4p1r, ham3000c02v1GanAes1l, ham3000c02v1PhaseAes1l, 
				ham3000c02v1GanAes1r, ham3000c02v1PhaseAes1r, ham3000c02v1GanAes2l, ham3000c02v1PhaseAes2l, ham3000c02v1GanAes2r, 
				ham3000c02v1PhaseAes2r, ham3000c02v1DelayG1p0l, ham3000c02v1DelayG1p0r, ham3000c02v1DelayG1p1l, ham3000c02v1DelayG1p1r, 
				ham3000c02v1DelayG2p0l, ham3000c02v1DelayG2p0r, ham3000c02v1DelayG2p1l, ham3000c02v1DelayG2p1r, ham3000c02v1DelayG3p0l, 
				ham3000c02v1DelayG3p0r, ham3000c02v1DelayG3p1l, ham3000c02v1DelayG3p1r, ham3000c02v1DelayG4p0l, ham3000c02v1DelayG4p0r, 
				ham3000c02v1DelayG4p1l, ham3000c02v1DelayG4p1r, ham3000c02v1DelayAes1l, ham3000c02v1DelayAes1r, ham3000c02v1DelayAes2l, 
				ham3000c02v1DelayAes2r, ham3000c02v1StatFlash, ham3000c02v1NoSignalMain, ham3000c02v1NoSignalMainTrapEnable, ham3000c02v1UnlockMain, 
				ham3000c02v1UnlockMainTrapEnable, ham3000c02v1EdhErrorMain, ham3000c02v1EdhErrorMainTrapEnable, ham3000c02v1NoSignalAux, ham3000c02v1UnlockAux, 
				ham3000c02v1EdhErrorAux, ham3000c02v1RefAbsent, ham3000c02v1RefAbsentTrapEnable, ham3000c02v1RefUnlock, ham3000c02v1RefUnlockTrapEnable, 
				ham3000c02v1FormatMainIn, ham3000c02v1FormatAuxIn, ham3000c02v1FormatRef, ham3000c02v1FormatMainTx, ham3000c02v1SigDelay, 
				ham3000c02v1Gr1MainPres, ham3000c02v1Gr1MainPresTrapEnable, ham3000c02v1Gr2MainPres, ham3000c02v1Gr2MainPresTrapEnable, ham3000c02v1Gr3MainPres, 
				ham3000c02v1Gr3MainPresTrapEnable, ham3000c02v1Gr4MainPres, ham3000c02v1Gr4MainPresTrapEnable, ham3000c02v1Gr1AuxPres, ham3000c02v1Gr2AuxPres, 
				ham3000c02v1Gr3AuxPres, ham3000c02v1Gr4AuxPres, ham3000c02v1Aes1Ok, ham3000c02v1Aes1Frq, ham3000c02v1Aes2Ok, 
				ham3000c02v1Aes2Frq, ham3000c02v1AudStatMain, ham3000c02v1AudStatMainTrapEnable, ham3000c02v1AudStatAux, ham3000c02v1AudStatAuxTrapEnable, 
				ham3000c02v1AudStatAes1, ham3000c02v1AudStatAes1TrapEnable, ham3000c02v1AudStatAes2, ham3000c02v1AudStatAes2TrapEnable, ham3000c02v1AudStatAnlg1, 
				ham3000c02v1AudStatAnlg1TrapEnable, ham3000c02v1AudStatAnlg2, ham3000c02v1AudStatAnlg2TrapEnable, ham3000c02v1OvldPgmOut, ham3000c02v1OvldPgmOutTrapEnable, 
				ham3000c02v1OvldAes1Out, ham3000c02v1OvldAes1OutTrapEnable, ham3000c02v1OvldAes2Out, ham3000c02v1OvldAes2OutTrapEnable, ham3000c02v1SilPgmOut, 
				ham3000c02v1SilPgmOutTrapEnable, ham3000c02v1SilAes1Out, ham3000c02v1SilAes1OutTrapEnable, ham3000c02v1SilAes2Out, ham3000c02v1SilAes2OutTrapEnable, 
				ham3000c02v1SerialNo, ham3000c02v1SavePreset, ham3000c02v1VidAuxSel }
			STATUS current
			DESCRIPTION
				"Module HAM3000C02V1 Group"
			::= { varGroups 407601 }

		-- 1.3.6.1.4.1.10106.2.3.1.407701
		ham3000c03v1ModuleGroup OBJECT-GROUP
			OBJECTS {ham3000c03v1Index, ham3000c03v1ActivePreset, ham3000c03v1LoadPreset, ham3000c03v1SynchroMode, ham3000c03v1FailMode, 
				ham3000c03v1DelayMode, ham3000c03v1HDelay, ham3000c03v1FrameDelay, ham3000c03v1VDelay, ham3000c03v1MuxAuxC1, 
				ham3000c03v1MuxAuxC2, ham3000c03v1MuxAuxC3, ham3000c03v1MuxAuxC4, ham3000c03v1FullScaleLev, ham3000c03v1OvldLevel, 
				ham3000c03v1SilenceLevel, ham3000c03v1SilenceTime, ham3000c03v1Gen1PipsTone, ham3000c03v1Gen2PipsTone, ham3000c03v1MediasGen1, 
				ham3000c03v1MediasGen2, ham3000c03v1FreqPips1, ham3000c03v1FreqPips2, ham3000c03v1LevelPips1, ham3000c03v1LevelPips2, 
				ham3000c03v1NPipsHour, ham3000c03v1NPipsHalf, ham3000c03v1ShortPerHour, ham3000c03v1ShortPerHalf, ham3000c03v1LongPerHour, 
				ham3000c03v1LongPerHalf, ham3000c03v1EmbG1p0l, ham3000c03v1EmbG1p0lMonPh, ham3000c03v1EmbG1p0lMono, ham3000c03v1EmbG1p0r, 
				ham3000c03v1EmbG1p0rMonPh, ham3000c03v1EmbG1p0rMono, ham3000c03v1EmbG1p1l, ham3000c03v1EmbG1p1lMonPh, ham3000c03v1EmbG1p1lMono, 
				ham3000c03v1EmbG1p1r, ham3000c03v1EmbG1p1rMonPh, ham3000c03v1EmbG1p1rMono, ham3000c03v1EmbG2p0l, ham3000c03v1EmbG2p0lMonPh, 
				ham3000c03v1EmbG2p0lMono, ham3000c03v1EmbG2p0r, ham3000c03v1EmbG2p0rMonPh, ham3000c03v1EmbG2p0rMono, ham3000c03v1EmbG2p1l, 
				ham3000c03v1EmbG2p1lMonPh, ham3000c03v1EmbG2p1lMono, ham3000c03v1EmbG2p1r, ham3000c03v1EmbG2p1rMonPh, ham3000c03v1EmbG2p1rMono, 
				ham3000c03v1EmbG3p0l, ham3000c03v1EmbG3p0lMonPh, ham3000c03v1EmbG3p0lMono, ham3000c03v1EmbG3p0r, ham3000c03v1EmbG3p0rMonPh, 
				ham3000c03v1EmbG3p0rMono, ham3000c03v1EmbG3p1l, ham3000c03v1EmbG3p1lMonPh, ham3000c03v1EmbG3p1lMono, ham3000c03v1EmbG3p1r, 
				ham3000c03v1EmbG3p1rMonPh, ham3000c03v1EmbG3p1rMono, ham3000c03v1EmbG4p0l, ham3000c03v1EmbG4p0lMonPh, ham3000c03v1EmbG4p0lMono, 
				ham3000c03v1EmbG4p0r, ham3000c03v1EmbG4p0rMonPh, ham3000c03v1EmbG4p0rMono, ham3000c03v1EmbG4p1l, ham3000c03v1EmbG4p1lMonPh, 
				ham3000c03v1EmbG4p1lMono, ham3000c03v1EmbG4p1r, ham3000c03v1EmbG4p1rMonPh, ham3000c03v1EmbG4p1rMono, ham3000c03v1AesOut1L, 
				ham3000c03v1AesOut1lMonPh, ham3000c03v1AesOut1lMono, ham3000c03v1AesOut1R, ham3000c03v1AesOut1rMonPh, ham3000c03v1AesOut1rMono, 
				ham3000c03v1AesOut2L, ham3000c03v1AesOut2lMonPh, ham3000c03v1AesOut2lMono, ham3000c03v1AesOut2R, ham3000c03v1AesOut2rMonPh, 
				ham3000c03v1AesOut2rMono, ham3000c03v1AnalogOut1L, ham3000c03v1AnlOut1lMonPh, ham3000c03v1AnlgOut1lMono, ham3000c03v1AnalogOut1R, 
				ham3000c03v1AnlOut1rMonPh, ham3000c03v1AnlgOut1rMono, ham3000c03v1AnalogOut2L, ham3000c03v1AnlOut2lMonPh, ham3000c03v1AnlgOut2lMono, 
				ham3000c03v1AnalogOut2R, ham3000c03v1AnlOut2rMonPh, ham3000c03v1AnlgOut2rMono, ham3000c03v1GanG1p0l, ham3000c03v1PhaseG1p0l, 
				ham3000c03v1GanG1p0r, ham3000c03v1PhaseG1p0r, ham3000c03v1GanG1p1l, ham3000c03v1PhaseG1p1l, ham3000c03v1GanG1p1r, 
				ham3000c03v1PhaseG1p1r, ham3000c03v1GanG2p0l, ham3000c03v1PhaseG2p0l, ham3000c03v1GanG2p0r, ham3000c03v1PhaseG2p0r, 
				ham3000c03v1GanG2p1l, ham3000c03v1PhaseG2p1l, ham3000c03v1GanG2p1r, ham3000c03v1PhaseG2p1r, ham3000c03v1GanG3p0l, 
				ham3000c03v1PhaseG3p0l, ham3000c03v1GanG3p0r, ham3000c03v1PhaseG3p0r, ham3000c03v1GanG3p1l, ham3000c03v1PhaseG3p1l, 
				ham3000c03v1GanG3p1r, ham3000c03v1PhaseG3p1r, ham3000c03v1GanG4p0l, ham3000c03v1PhaseG4p0l, ham3000c03v1GanG4p0r, 
				ham3000c03v1PhaseG4p0r, ham3000c03v1GanG4p1l, ham3000c03v1PhaseG4p1l, ham3000c03v1GanG4p1r, ham3000c03v1PhaseG4p1r, 
				ham3000c03v1GanAes1l, ham3000c03v1PhaseAes1l, ham3000c03v1GanAes1r, ham3000c03v1PhaseAes1r, ham3000c03v1GanAes2l, 
				ham3000c03v1PhaseAes2l, ham3000c03v1GanAes2r, ham3000c03v1PhaseAes2r, ham3000c03v1GanAnlg1l, ham3000c03v1PhaseAnlg1l, 
				ham3000c03v1GanAnlg1r, ham3000c03v1PhaseAnlg1r, ham3000c03v1GanAnlg2l, ham3000c03v1PhaseAnlg2l, ham3000c03v1GanAnlg2r, 
				ham3000c03v1PhaseAnlg2r, ham3000c03v1DelayG1p0l, ham3000c03v1DelayG1p0r, ham3000c03v1DelayG1p1l, ham3000c03v1DelayG1p1r, 
				ham3000c03v1DelayG2p0l, ham3000c03v1DelayG2p0r, ham3000c03v1DelayG2p1l, ham3000c03v1DelayG2p1r, ham3000c03v1DelayG3p0l, 
				ham3000c03v1DelayG3p0r, ham3000c03v1DelayG3p1l, ham3000c03v1DelayG3p1r, ham3000c03v1DelayG4p0l, ham3000c03v1DelayG4p0r, 
				ham3000c03v1DelayG4p1l, ham3000c03v1DelayG4p1r, ham3000c03v1DelayAes1l, ham3000c03v1DelayAes1r, ham3000c03v1DelayAes2l, 
				ham3000c03v1DelayAes2r, ham3000c03v1DelayAnlg1l, ham3000c03v1DelayAnlg1r, ham3000c03v1DelayAnlg2l, ham3000c03v1DelayAnlg2r, 
				ham3000c03v1StatFlash, ham3000c03v1NoSignalMain, ham3000c03v1NoSignalMainTrapEnable, ham3000c03v1UnlockMain, ham3000c03v1UnlockMainTrapEnable, 
				ham3000c03v1EdhErrorMain, ham3000c03v1EdhErrorMainTrapEnable, ham3000c03v1NoSignalAux, ham3000c03v1UnlockAux, ham3000c03v1EdhErrorAux, 
				ham3000c03v1RefAbsent, ham3000c03v1RefAbsentTrapEnable, ham3000c03v1RefUnlock, ham3000c03v1RefUnlockTrapEnable, ham3000c03v1FormatMainIn, 
				ham3000c03v1FormatAuxIn, ham3000c03v1FormatRef, ham3000c03v1FormatMainTx, ham3000c03v1SigDelay, ham3000c03v1Gr1MainPres, 
				ham3000c03v1Gr1MainPresTrapEnable, ham3000c03v1Gr2MainPres, ham3000c03v1Gr2MainPresTrapEnable, ham3000c03v1Gr3MainPres, ham3000c03v1Gr3MainPresTrapEnable, 
				ham3000c03v1Gr4MainPres, ham3000c03v1Gr4MainPresTrapEnable, ham3000c03v1Gr1AuxPres, ham3000c03v1Gr2AuxPres, ham3000c03v1Gr3AuxPres, 
				ham3000c03v1Gr4AuxPres, ham3000c03v1Aes1Ok, ham3000c03v1Aes1Frq, ham3000c03v1Aes2Ok, ham3000c03v1Aes2Frq, 
				ham3000c03v1AudStatMain, ham3000c03v1AudStatMainTrapEnable, ham3000c03v1AudStatAux, ham3000c03v1AudStatAuxTrapEnable, ham3000c03v1AudStatAes1, 
				ham3000c03v1AudStatAes1TrapEnable, ham3000c03v1AudStatAes2, ham3000c03v1AudStatAes2TrapEnable, ham3000c03v1OvldPgmOut, ham3000c03v1OvldPgmOutTrapEnable, 
				ham3000c03v1OvldAes1Out, ham3000c03v1OvldAes1OutTrapEnable, ham3000c03v1OvldAes2Out, ham3000c03v1OvldAes2OutTrapEnable, ham3000c03v1OvldAnlg1Out, 
				ham3000c03v1OvldAnlg1OutTrapEnable, ham3000c03v1OvldAnlg2Out, ham3000c03v1OvldAnlg2OutTrapEnable, ham3000c03v1SilPgmOut, ham3000c03v1SilPgmOutTrapEnable, 
				ham3000c03v1SilAes1Out, ham3000c03v1SilAes1OutTrapEnable, ham3000c03v1SilAes2Out, ham3000c03v1SilAes2OutTrapEnable, ham3000c03v1SilAnlg1Out, 
				ham3000c03v1SilAnlg1OutTrapEnable, ham3000c03v1SilAnlg2Out, ham3000c03v1SilAnlg2OutTrapEnable, ham3000c03v1SerialNo, ham3000c03v1SavePreset, 
				ham3000c03v1VidAuxSel }
			STATUS current
			DESCRIPTION
				"Module HAM3000C03V1 Group"
			::= { varGroups 407701 }

		-- 1.3.6.1.4.1.10106.2.3.1.412201
		hop3147c02v1ModuleGroup OBJECT-GROUP
			OBJECTS {hop3147c02v1Index, hop3147c02v1ActivePreset, hop3147c02v1LoadPreset, hop3147c02v1SavePreset, hop3147c02v1TxtInsEna1, 
				hop3147c02v1TxtInsEna2, hop3147c02v1Op47InsEna, hop3147c02v1TxtCleanEna1, hop3147c02v1TxtCleanEna2, hop3147c02v1Op47CleanEna, 
				hop3147c02v1Gpo8SigFail, hop3147c02v1Op47PckInsLin, hop3147c02v1TxtInsLine1, hop3147c02v1TxtInsLine2, hop3147c02v1TxtRdLine, 
				hop3147c02v1TxtRdEna, hop3147c02v1InvertGpi1Pol, hop3147c02v1InvertGpi2Pol, hop3147c02v1InvertGpi3Pol, hop3147c02v1InvertGpi4Pol, 
				hop3147c02v1InvertGpi5Pol, hop3147c02v1InvertGpi6Pol, hop3147c02v1InvertGpi7Pol, hop3147c02v1InvertGpi8Pol, hop3147c02v1InvertGpo1Pol, 
				hop3147c02v1InvertGpo2Pol, hop3147c02v1InvertGpo3Pol, hop3147c02v1InvertGpo4Pol, hop3147c02v1InvertGpo5Pol, hop3147c02v1InvertGpo6Pol, 
				hop3147c02v1InvertGpo7Pol, hop3147c02v1InvertGpo8Pol, hop3147c02v1TxtInsA, hop3147c02v1TxtInsB, hop3147c02v1TxtInsFrstLin, 
				hop3147c02v1TxtInsHidenCh, hop3147c02v1TxtInsPage, hop3147c02v1TxtBridgeEn, hop3147c02v1InsAudioEn, hop3147c02v1InsAudPair, 
				hop3147c02v1RdAudEn, hop3147c02v1RdAudChn, hop3147c02v1CleanAudChnEn, hop3147c02v1GposSrc, hop3147c02v1VitcBridgeEn, 
				hop3147c02v1KeepSdLinVitc, hop3147c02v1SdLineVitc, hop3147c02v1KeepDupVitc, hop3147c02v1DupVitc, hop3147c02v1ViiInsEn, 
				hop3147c02v1WssInsEn, hop3147c02v1AfdInsEn, hop3147c02v1AfdAr, hop3147c02v1AfdD, hop3147c02v1AncInsL1En, 
				hop3147c02v1AncInsL2En, hop3147c02v1AncInsActVid, hop3147c02v1AncInsLumNCr, hop3147c02v1AncInsPckNum, hop3147c02v1AncInsL1, 
				hop3147c02v1AncInsL2, hop3147c02v1AncInsRepet, hop3147c02v1GpisInvPrst1, hop3147c02v1GpisInvPrst2, hop3147c02v1GpisInvPrst3, 
				hop3147c02v1GpisInvPrst4, hop3147c02v1GpisInvPrst5, hop3147c02v1GpisInvPrst6, hop3147c02v1GpisInvPrst7, hop3147c02v1GpisInvPrst8, 
				hop3147c02v1TxtBridgeEn0, hop3147c02v1TxtBridgeEn1, hop3147c02v1TxtBridgeEn2, hop3147c02v1TxtBridgeEn3, hop3147c02v1TxtBridgeEn4, 
				hop3147c02v1TxtBridgeEn5, hop3147c02v1TxtBridgeEn6, hop3147c02v1TxtBridgeEn7, hop3147c02v1TxtBridgeEn8, hop3147c02v1TxtBridgeEn9, 
				hop3147c02v1TxtBridgeEn10, hop3147c02v1TxtBridgeEn11, hop3147c02v1TxtBridgeEn12, hop3147c02v1TxtBridgeEn13, hop3147c02v1TxtBridgeEn14, 
				hop3147c02v1TxtBridgeEn15, hop3147c02v1TxtBridgeEn16, hop3147c02v1TxtBridgeEn17, hop3147c02v1TxtBridgeEn18, hop3147c02v1TxtBridgeEn19, 
				hop3147c02v1TxtBridgeEn20, hop3147c02v1TxtBridgeEn21, hop3147c02v1TxtBridgeEn22, hop3147c02v1TxtBridgeEn23, hop3147c02v1TxtBridgeEn24, 
				hop3147c02v1TxtBridgeEn25, hop3147c02v1TxtBridgeEn26, hop3147c02v1TxtBridgeEn27, hop3147c02v1TxtBridgeEn28, hop3147c02v1TxtBridgeEn29, 
				hop3147c02v1TxtBridgeEn30, hop3147c02v1TxtBridgeEn31, hop3147c02v1TxtBridge0, hop3147c02v1TxtBridge1, hop3147c02v1TxtBridge2, 
				hop3147c02v1TxtBridge3, hop3147c02v1TxtBridge4, hop3147c02v1TxtBridge5, hop3147c02v1TxtBridge6, hop3147c02v1TxtBridge7, 
				hop3147c02v1TxtBridge8, hop3147c02v1TxtBridge9, hop3147c02v1TxtBridge10, hop3147c02v1TxtBridge11, hop3147c02v1TxtBridge12, 
				hop3147c02v1TxtBridge13, hop3147c02v1TxtBridge14, hop3147c02v1TxtBridge15, hop3147c02v1TxtBridge16, hop3147c02v1TxtBridge17, 
				hop3147c02v1TxtBridge18, hop3147c02v1TxtBridge19, hop3147c02v1TxtBridge20, hop3147c02v1TxtBridge21, hop3147c02v1TxtBridge22, 
				hop3147c02v1TxtBridge23, hop3147c02v1TxtBridge24, hop3147c02v1TxtBridge25, hop3147c02v1TxtBridge26, hop3147c02v1TxtBridge27, 
				hop3147c02v1TxtBridge28, hop3147c02v1TxtBridge29, hop3147c02v1TxtBridge30, hop3147c02v1TxtBridge31, hop3147c02v1TxtBridgeOp47, 
				hop3147c02v1TxtFail, hop3147c02v1TxtFailTrapEnable, hop3147c02v1TxtInsFail, hop3147c02v1TxtInsFailTrapEnable, hop3147c02v1AudioFail, 
				hop3147c02v1AudioFailTrapEnable, hop3147c02v1AudioInsFail, hop3147c02v1AudioInsFailTrapEnable, hop3147c02v1ViiInsFail, hop3147c02v1ViiInsFailTrapEnable, 
				hop3147c02v1WssInsFail, hop3147c02v1WssInsFailTrapEnable, hop3147c02v1AfdInsFail, hop3147c02v1AfdInsFailTrapEnable, hop3147c02v1NoSignal0, 
				hop3147c02v1NoSignal0TrapEnable, hop3147c02v1Unlocked0, hop3147c02v1Unlocked0TrapEnable, hop3147c02v1EdhCrc0, hop3147c02v1EdhCrc0TrapEnable, 
				hop3147c02v1Format0, hop3147c02v1NoSignal1, hop3147c02v1NoSignal1TrapEnable, hop3147c02v1Unlocked1, hop3147c02v1Unlocked1TrapEnable, 
				hop3147c02v1EdhCrc1, hop3147c02v1EdhCrc1TrapEnable, hop3147c02v1Format1, hop3147c02v1Gpi1, hop3147c02v1Gpi1TrapEnable, 
				hop3147c02v1Gpi2, hop3147c02v1Gpi2TrapEnable, hop3147c02v1Gpi3, hop3147c02v1Gpi3TrapEnable, hop3147c02v1Gpi4, 
				hop3147c02v1Gpi4TrapEnable, hop3147c02v1Gpi5, hop3147c02v1Gpi5TrapEnable, hop3147c02v1Gpi6, hop3147c02v1Gpi6TrapEnable, 
				hop3147c02v1Gpi7, hop3147c02v1Gpi7TrapEnable, hop3147c02v1Gpi8, hop3147c02v1Gpi8TrapEnable, hop3147c02v1Gpo1, 
				hop3147c02v1Gpo1TrapEnable, hop3147c02v1Gpo2, hop3147c02v1Gpo2TrapEnable, hop3147c02v1Gpo3, hop3147c02v1Gpo3TrapEnable, 
				hop3147c02v1Gpo4, hop3147c02v1Gpo4TrapEnable, hop3147c02v1Gpo5, hop3147c02v1Gpo5TrapEnable, hop3147c02v1Gpo6, 
				hop3147c02v1Gpo6TrapEnable, hop3147c02v1Gpo7, hop3147c02v1Gpo7TrapEnable, hop3147c02v1Gpo8, hop3147c02v1Gpo8TrapEnable, 
				hop3147c02v1VitcAtcPres, hop3147c02v1VitcAtcPresTrapEnable, hop3147c02v1TxtAuxPres, hop3147c02v1TxtAuxPresTrapEnable, hop3147c02v1TxtPres, 
				hop3147c02v1TxtPresTrapEnable, hop3147c02v1AncInsL1Ok, hop3147c02v1AncInsL2Ok, hop3147c02v1SerialNo, hop3147c02v1SplStartInmEn, 
				hop3147c02v1SplEndInmEn, hop3147c02v1SplStartNorEn, hop3147c02v1SplEndNorEn, hop3147c02v1Scte104StNDyn, hop3147c02v1Scte104AretTx, 
				hop3147c02v1Scte104RxAck, hop3147c02v1Scte104RxAsEn, hop3147c02v1Scte104RxAsFi, hop3147c02v1Scte104TxAsId, hop3147c02v1Scte104Line, 
				hop3147c02v1Scte104PreRoll, hop3147c02v1Scte104TxBrkds, hop3147c02v1Scte104TxBrkdd, hop3147c02v1Scte104InsF, hop3147c02v1Scte104RxF, 
				hop3147c02v1Scte104Status, hop3147c02v1Scte104AretRx, hop3147c02v1Scte104RxPck, hop3147c02v1Scte104RxAsId, hop3147c02v1Scte104RxPrRo, 
				hop3147c02v1Scte104RxBrkd, hop3147c02v1Scte104ContRx, hop3147c02v1LtcInsEn, hop3147c02v1DtmfInsEn, hop3147c02v1DtmfGpi5En, 
				hop3147c02v1DtmfGpi6En, hop3147c02v1DtmfGpi7En, hop3147c02v1DtmfGpi8En, hop3147c02v1DtmfChannel, hop3147c02v1DtmfPairEn, 
				hop3147c02v1DtmfLevel, hop3147c02v1DtmfCode11, hop3147c02v1DtmfCode12, hop3147c02v1DtmfCode13, hop3147c02v1DtmfCode14, 
				hop3147c02v1DtmfCode21, hop3147c02v1DtmfCode22, hop3147c02v1DtmfCode23, hop3147c02v1DtmfCode24, hop3147c02v1DtmfCode31, 
				hop3147c02v1DtmfCode32, hop3147c02v1DtmfCode33, hop3147c02v1DtmfCode34, hop3147c02v1DtmfCode41, hop3147c02v1DtmfCode42, 
				hop3147c02v1DtmfCode43, hop3147c02v1DtmfCode44, hop3147c02v1InsCode1, hop3147c02v1InsCode2, hop3147c02v1InsCode3, 
				hop3147c02v1InsCode4, hop3147c02v1Scte104Ins, hop3147c02v1SplStInmInEn, hop3147c02v1SplStEndInEn, hop3147c02v1Gpi7SplStaOn, 
				hop3147c02v1Gpi8SplStaOff }
			STATUS current
			DESCRIPTION
				"Module HOP3147C02V1 Group"
			::= { varGroups 412201 }

		-- 1.3.6.1.4.1.10106.2.3.1.413901
		kbd3160c01v1ModuleGroup OBJECT-GROUP
			OBJECTS {kbd3160c01v1Index, kbd3160c01v1BeepEna, kbd3160c01v1Brightness, kbd3160c01v1Gpo1, kbd3160c01v1Gpo2, 
				kbd3160c01v1Gpo3, kbd3160c01v1Gpo4, kbd3160c01v1Gpo5, kbd3160c01v1Gpo6, kbd3160c01v1Gpo7, 
				kbd3160c01v1Gpo8, kbd3160c01v1Gpo9, kbd3160c01v1Gpo10, kbd3160c01v1Gpo11, kbd3160c01v1Gpo12, 
				kbd3160c01v1Gpo13, kbd3160c01v1Gpo14, kbd3160c01v1Gpo15, kbd3160c01v1Gpo16, kbd3160c01v1Gpi1, 
				kbd3160c01v1Gpi2, kbd3160c01v1Gpi3, kbd3160c01v1Gpi4, kbd3160c01v1Gpi5, kbd3160c01v1Gpi6, 
				kbd3160c01v1Gpi7, kbd3160c01v1Gpi8, kbd3160c01v1Gpi9, kbd3160c01v1Gpi10, kbd3160c01v1Gpi11, 
				kbd3160c01v1Gpi12, kbd3160c01v1Gpi13, kbd3160c01v1Gpi14, kbd3160c01v1Gpi15, kbd3160c01v1Gpi16, 
				kbd3160c01v1Psu0Fail, kbd3160c01v1Psu1Fail, kbd3160c01v1SerialNo }
			STATUS current
			DESCRIPTION
				"Module KBD3160C01V1 Group"
			::= { varGroups 413901 }

		-- 1.3.6.1.4.1.10106.2.3.1.415501
		act3000c01v1ModuleGroup OBJECT-GROUP
			OBJECTS {act3000c01v1Index, act3000c01v1ActivePreset, act3000c01v1LoadPreset, act3000c01v1SavePreset, act3000c01v1StateSel, 
				act3000c01v1StateSelTrapEnable, act3000c01v1In1StChange, act3000c01v1In2StChange, act3000c01v1Gpi1StChange, act3000c01v1Gpi2StChange, 
				act3000c01v1InputChange, act3000c01v1StatusChange, act3000c01v1SwitchMode, act3000c01v1SwitchModeTrapEnable, act3000c01v1StateAMapOut, 
				act3000c01v1StateAMapGpo, act3000c01v1StateBMapOut, act3000c01v1StateBMapGpo, act3000c01v1Holdoff, act3000c01v1ActPer1, 
				act3000c01v1DeactPer1, act3000c01v1ActPer2, act3000c01v1DeactPer2, act3000c01v1SilenceLevel, act3000c01v1OvldLevel, 
				act3000c01v1ClippingLevel, act3000c01v1AntiphLevel, act3000c01v1SilFailTim, act3000c01v1OvldFailTim, act3000c01v1AntiphFailTim, 
				act3000c01v1GpiFailTim, act3000c01v1MeasSil1, act3000c01v1MeasSil2, act3000c01v1MeasOvld1, act3000c01v1MeasOvld2, 
				act3000c01v1LoudSel, act3000c01v1PairIn1, act3000c01v1PairIn2, act3000c01v1GpoCfg, act3000c01v1SmoothDel, 
				act3000c01v1SmoothDelTime, act3000c01v1Delay1l, act3000c01v1Gain1l, act3000c01v1Phase1l, act3000c01v1Delay1r, 
				act3000c01v1Gain1r, act3000c01v1Phase1r, act3000c01v1Delay2l, act3000c01v1Gain2l, act3000c01v1Phase2l, 
				act3000c01v1Delay2r, act3000c01v1Gain2r, act3000c01v1Phase2r, act3000c01v1StatFlash, act3000c01v1StatusIn1, 
				act3000c01v1StatusIn1TrapEnable, act3000c01v1StatusIn2, act3000c01v1StatusIn2TrapEnable, act3000c01v1StatusIn1Ext, act3000c01v1StatusIn1ExtTrapEnable, 
				act3000c01v1StatusIn2Ext, act3000c01v1StatusIn2ExtTrapEnable, act3000c01v1StatusIn1Clip, act3000c01v1StatusIn1ClipTrapEnable, act3000c01v1StatusIn2Clip, 
				act3000c01v1StatusIn2ClipTrapEnable, act3000c01v1SelOut1, act3000c01v1SelOut1TrapEnable, act3000c01v1SelOut2, act3000c01v1SelOut2TrapEnable, 
				act3000c01v1Gpo1Out, act3000c01v1Gpo2Out, act3000c01v1Gpi1Stat, act3000c01v1Gpi1StatTrapEnable, act3000c01v1FailSil1l, 
				act3000c01v1FailSil1lTrapEnable, act3000c01v1FailOvld1l, act3000c01v1FailOvld1lTrapEnable, act3000c01v1FailClip1l, act3000c01v1FailClip1lTrapEnable, 
				act3000c01v1FailAnti1, act3000c01v1FailAnti1TrapEnable, act3000c01v1FailSil1r, act3000c01v1FailSil1rTrapEnable, act3000c01v1FailOvld1r, 
				act3000c01v1FailOvld1rTrapEnable, act3000c01v1FailClip1r, act3000c01v1FailClip1rTrapEnable, act3000c01v1FailExt1, act3000c01v1FailExt1TrapEnable, 
				act3000c01v1FailSil2l, act3000c01v1FailSil2lTrapEnable, act3000c01v1FailOvld2l, act3000c01v1FailOvld2lTrapEnable, act3000c01v1FailClip2l, 
				act3000c01v1FailClip2lTrapEnable, act3000c01v1FailAnti2, act3000c01v1FailAnti2TrapEnable, act3000c01v1FailSil2r, act3000c01v1FailSil2rTrapEnable, 
				act3000c01v1FailOvld2r, act3000c01v1FailOvld2rTrapEnable, act3000c01v1FailClip2r, act3000c01v1FailClip2rTrapEnable, act3000c01v1FailExt2, 
				act3000c01v1FailExt2TrapEnable, act3000c01v1CurrentSmooth, act3000c01v1SerialNo }
			STATUS current
			DESCRIPTION
				"Module ACT3000C01V1 Group"
			::= { varGroups 415501 }

		-- 1.3.6.1.4.1.10106.2.3.1.416301
		hvd2000c01v1ModuleGroup OBJECT-GROUP
			OBJECTS {hvd2000c01v1Index, hvd2000c01v1NoSig, hvd2000c01v1NoSigTrapEnable, hvd2000c01v1Unlock, hvd2000c01v1UnlockTrapEnable, 
				hvd2000c01v1Hd, hvd2000c01v1SerialNo }
			STATUS current
			DESCRIPTION
				"Module HVD2000C01V1 Group"
			::= { varGroups 416301 }

		-- 1.3.6.1.4.1.10106.2.3.1.420401
		kbd3160c02v1ModuleGroup OBJECT-GROUP
			OBJECTS {kbd3160c02v1Index, kbd3160c02v1BeepEna, kbd3160c02v1Brightness, kbd3160c02v1Gpo1, kbd3160c02v1Gpo2, 
				kbd3160c02v1Gpo3, kbd3160c02v1Gpo4, kbd3160c02v1Gpo5, kbd3160c02v1Gpo6, kbd3160c02v1Gpo7, 
				kbd3160c02v1Gpo8, kbd3160c02v1Gpo9, kbd3160c02v1Gpo10, kbd3160c02v1Gpo11, kbd3160c02v1Gpo12, 
				kbd3160c02v1Gpo13, kbd3160c02v1Gpo14, kbd3160c02v1Gpo15, kbd3160c02v1Gpo16, kbd3160c02v1Gpi1, 
				kbd3160c02v1Gpi2, kbd3160c02v1Gpi3, kbd3160c02v1Gpi4, kbd3160c02v1Gpi5, kbd3160c02v1Gpi6, 
				kbd3160c02v1Gpi7, kbd3160c02v1Gpi8, kbd3160c02v1Gpi9, kbd3160c02v1Gpi10, kbd3160c02v1Gpi11, 
				kbd3160c02v1Gpi12, kbd3160c02v1Gpi13, kbd3160c02v1Gpi14, kbd3160c02v1Gpi15, kbd3160c02v1Gpi16, 
				kbd3160c02v1Psu0Fail, kbd3160c02v1Psu1Fail, kbd3160c02v1SerialNo }
			STATUS current
			DESCRIPTION
				"Module KBD3160C02V1 Group"
			::= { varGroups 420401 }

		-- 1.3.6.1.4.1.10106.2.3.1.422601
		tsa3000c01v1ModuleGroup OBJECT-GROUP
			OBJECTS {tsa3000c01v1Index, tsa3000c01v1Mode, tsa3000c01v1ModeTrapEnable, tsa3000c01v1NullPckRtp, tsa3000c01v1NarrowPllBw, 
				tsa3000c01v1Buzzer, tsa3000c01v1GpioMode, tsa3000c01v1InputStChange, tsa3000c01v1InputChange, tsa3000c01v1EnaAsi1, 
				tsa3000c01v1EnaAsi2, tsa3000c01v1EnaIp1, tsa3000c01v1EnaIp2, tsa3000c01v1SelectedInput, tsa3000c01v1SelectedInputTrapEnable, 
				tsa3000c01v1PingEnable1, tsa3000c01v1IpLinkFailEn, tsa3000c01v1IpDestFailEn, tsa3000c01v1MaxTimeOut, tsa3000c01v1StatReset, 
				tsa3000c01v1StatSel, tsa3000c01v1StatMode, tsa3000c01v1IgmpVersion, tsa3000c01v1EthMode, tsa3000c01v1PckDelAsiIn1, 
				tsa3000c01v1PckDelAsiIn2, tsa3000c01v1PckDelIpIn1, tsa3000c01v1PckDelIpIn2, tsa3000c01v1AsiIn1Prior0, tsa3000c01v1AsiIn2Prior0, 
				tsa3000c01v1IpIn1Prior0, tsa3000c01v1IpIn2Prior0, tsa3000c01v1BitrateEn, tsa3000c01v1Bitrate, tsa3000c01v1FilterEn, 
				tsa3000c01v1PatPidsEn, tsa3000c01v1CatPidsEn, tsa3000c01v1PmtPrgmEn, tsa3000c01v1RsrvedPidsEn, tsa3000c01v1NullPckEn, 
				tsa3000c01v1InvertFilter, tsa3000c01v1PmtPrgmEn0, tsa3000c01v1PmtPrgmEn1, tsa3000c01v1PmtPrgmEn2, tsa3000c01v1PmtPrgmEn3, 
				tsa3000c01v1PmtPrgmEn4, tsa3000c01v1PmtPrgmEn5, tsa3000c01v1PmtPrgmEn6, tsa3000c01v1PmtPrgmEn7, tsa3000c01v1PmtPrgmEn8, 
				tsa3000c01v1PmtPrgmEn9, tsa3000c01v1PmtPrgmEn10, tsa3000c01v1PmtPrgmEn11, tsa3000c01v1PmtPrgmEn12, tsa3000c01v1PmtPrgmEn13, 
				tsa3000c01v1PmtPrgmEn14, tsa3000c01v1PmtPrgmEn15, tsa3000c01v1PidPacketEn0, tsa3000c01v1PidPacketEn1, tsa3000c01v1PidPacketEn2, 
				tsa3000c01v1PidPacketEn3, tsa3000c01v1PidPacketEn4, tsa3000c01v1PidPacketEn5, tsa3000c01v1PidPacketEn6, tsa3000c01v1PidPacketEn7, 
				tsa3000c01v1PidPacketEn8, tsa3000c01v1PidPacketEn9, tsa3000c01v1PidPacketEn10, tsa3000c01v1PidPacketEn11, tsa3000c01v1PidPacketEn12, 
				tsa3000c01v1PidPacketEn13, tsa3000c01v1PidPacketEn14, tsa3000c01v1PidPacketEn15, tsa3000c01v1ActivePreset, tsa3000c01v1LoadPreset, 
				tsa3000c01v1SavePreset, tsa3000c01v1Str1UipDAdd3, tsa3000c01v1Str1UipDAdd2, tsa3000c01v1Str1UipDAdd1, tsa3000c01v1Str1UipDAdd0, 
				tsa3000c01v1Str1MipDAdd3, tsa3000c01v1Str1MipDAdd2, tsa3000c01v1Str1MipDAdd1, tsa3000c01v1Str1MipDAdd0, tsa3000c01v1Str1DPort, 
				tsa3000c01v1Str1FecEna, tsa3000c01v1Str1MulticEna, tsa3000c01v1VlanRx1Enable, tsa3000c01v1VlanRx1Id, tsa3000c01v1Str2UipDAdd3, 
				tsa3000c01v1Str2UipDAdd2, tsa3000c01v1Str2UipDAdd1, tsa3000c01v1Str2UipDAdd0, tsa3000c01v1Str2MipDAdd3, tsa3000c01v1Str2MipDAdd2, 
				tsa3000c01v1Str2MipDAdd1, tsa3000c01v1Str2MipDAdd0, tsa3000c01v1Str2DPort, tsa3000c01v1Str2FecEna, tsa3000c01v1Str2MulticEna, 
				tsa3000c01v1VlanRx2Enable, tsa3000c01v1VlanRx2Id, tsa3000c01v1LocalIpAdd3, tsa3000c01v1LocalIpAdd2, tsa3000c01v1LocalIpAdd1, 
				tsa3000c01v1LocalIpAdd0, tsa3000c01v1LocalIpMask3, tsa3000c01v1LocalIpMask2, tsa3000c01v1LocalIpMask1, tsa3000c01v1LocalIpMask0, 
				tsa3000c01v1LocalIpGway3, tsa3000c01v1LocalIpGway2, tsa3000c01v1LocalIpGway1, tsa3000c01v1LocalIpGway0, tsa3000c01v1Tx1UniEna, 
				tsa3000c01v1Tx1MultiEna, tsa3000c01v1Tx1UipAdd3, tsa3000c01v1Tx1UipAdd2, tsa3000c01v1Tx1UipAdd1, tsa3000c01v1Tx1UipAdd0, 
				tsa3000c01v1Tx1MipAdd3, tsa3000c01v1Tx1MipAdd2, tsa3000c01v1Tx1MipAdd1, tsa3000c01v1Tx1MipAdd0, tsa3000c01v1Tx1SPort, 
				tsa3000c01v1Tx1DPort, tsa3000c01v1VlanTxEnable1, tsa3000c01v1VlanTxPrior1, tsa3000c01v1VlanTxId1, tsa3000c01v1Tx1LParam, 
				tsa3000c01v1Tx1FecMode, tsa3000c01v1Tx1DParam, tsa3000c01v1Tx1TspkInIppk, tsa3000c01v1Tx1RowDelay, tsa3000c01v1Tx1ColDelay, 
				tsa3000c01v1LowCost1, tsa3000c01v1HighReliab1, tsa3000c01v1HighThroughp1, tsa3000c01v1LowDelay1, tsa3000c01v1Precedence1, 
				tsa3000c01v1Ttl1, tsa3000c01v1Str1IgmFAdd3, tsa3000c01v1Str1IgmFAdd2, tsa3000c01v1Str1IgmFAdd1, tsa3000c01v1Str1IgmFAdd0, 
				tsa3000c01v1Str2IgmFAdd3, tsa3000c01v1Str2IgmFAdd2, tsa3000c01v1Str2IgmFAdd1, tsa3000c01v1Str2IgmFAdd0, tsa3000c01v1PmtPrgm0, 
				tsa3000c01v1PmtPrgm1, tsa3000c01v1PmtPrgm2, tsa3000c01v1PmtPrgm3, tsa3000c01v1PmtPrgm4, tsa3000c01v1PmtPrgm5, 
				tsa3000c01v1PmtPrgm6, tsa3000c01v1PmtPrgm7, tsa3000c01v1PmtPrgm8, tsa3000c01v1PmtPrgm9, tsa3000c01v1PmtPrgm10, 
				tsa3000c01v1PmtPrgm11, tsa3000c01v1PmtPrgm12, tsa3000c01v1PmtPrgm13, tsa3000c01v1PmtPrgm14, tsa3000c01v1PmtPrgm15, 
				tsa3000c01v1Str1AipDAdd3, tsa3000c01v1Str1AipDAdd2, tsa3000c01v1Str1AipDAdd1, tsa3000c01v1Str1AipDAdd0, tsa3000c01v1Str1APortMsb, 
				tsa3000c01v1Str1APortLsb, tsa3000c01v1Str1IgmAAdd3, tsa3000c01v1Str1IgmAAdd2, tsa3000c01v1Str1IgmAAdd1, tsa3000c01v1Str1IgmAAdd0, 
				tsa3000c01v1Str2AipDAdd3, tsa3000c01v1Str2AipDAdd2, tsa3000c01v1Str2AipDAdd1, tsa3000c01v1Str2AipDAdd0, tsa3000c01v1Str2APortMsb, 
				tsa3000c01v1Str2APortLsb, tsa3000c01v1Str2IgmAAdd3, tsa3000c01v1Str2IgmAAdd2, tsa3000c01v1Str2IgmAAdd1, tsa3000c01v1Str2IgmAAdd0, 
				tsa3000c01v1PidPacket0, tsa3000c01v1PidPacket1, tsa3000c01v1PidPacket2, tsa3000c01v1PidPacket3, tsa3000c01v1PidPacket4, 
				tsa3000c01v1PidPacket5, tsa3000c01v1PidPacket6, tsa3000c01v1PidPacket7, tsa3000c01v1PidPacket8, tsa3000c01v1PidPacket9, 
				tsa3000c01v1PidPacket10, tsa3000c01v1PidPacket11, tsa3000c01v1PidPacket12, tsa3000c01v1PidPacket13, tsa3000c01v1PidPacket14, 
				tsa3000c01v1PidPacket15, tsa3000c01v1PatStat, tsa3000c01v1CatStat, tsa3000c01v1PmtPrgmStat0, tsa3000c01v1PmtPrgmStat1, 
				tsa3000c01v1PmtPrgmStat2, tsa3000c01v1PmtPrgmStat3, tsa3000c01v1PmtPrgmStat4, tsa3000c01v1PmtPrgmStat5, tsa3000c01v1PmtPrgmStat6, 
				tsa3000c01v1PmtPrgmStat7, tsa3000c01v1PmtPrgmStat8, tsa3000c01v1PmtPrgmStat9, tsa3000c01v1PmtPrgmStat10, tsa3000c01v1PmtPrgmStat11, 
				tsa3000c01v1PmtPrgmStat12, tsa3000c01v1PmtPrgmStat13, tsa3000c01v1PmtPrgmStat14, tsa3000c01v1PmtPrgmStat15, tsa3000c01v1BitrateUtil, 
				tsa3000c01v1OutFail, tsa3000c01v1AsiIn1Fail, tsa3000c01v1AsiIn1FailTrapEnable, tsa3000c01v1ExAsiIn1Fail, tsa3000c01v1ExAsiIn1FailTrapEnable, 
				tsa3000c01v1AsiIn2Fail, tsa3000c01v1AsiIn2FailTrapEnable, tsa3000c01v1ExAsiIn2Fail, tsa3000c01v1ExAsiIn2FailTrapEnable, tsa3000c01v1IpIn1Fail, 
				tsa3000c01v1IpIn1FailTrapEnable, tsa3000c01v1ExIpIn1Fail, tsa3000c01v1ExIpIn1FailTrapEnable, tsa3000c01v1IpIn2Fail, tsa3000c01v1IpIn2FailTrapEnable, 
				tsa3000c01v1ExIpIn2Fail, tsa3000c01v1ExIpIn2FailTrapEnable, tsa3000c01v1DestAvailable1, tsa3000c01v1BlindModStat1, tsa3000c01v1BlindModStat2, 
				tsa3000c01v1AsiIn1Delay, tsa3000c01v1AsiIn2Delay, tsa3000c01v1IpIn1Delay, tsa3000c01v1IpIn2Delay, tsa3000c01v1IpRxAddress3, 
				tsa3000c01v1IpRxAddress2, tsa3000c01v1IpRxAddress1, tsa3000c01v1IpRxAddress0, tsa3000c01v1IpRxPort, tsa3000c01v1LParam, 
				tsa3000c01v1FecMode, tsa3000c01v1PacketSize, tsa3000c01v1DParam, tsa3000c01v1TsPckInIpPck, tsa3000c01v1PacketRate, 
				tsa3000c01v1TimeSinceReset, tsa3000c01v1LostIpPck, tsa3000c01v1RecoveredIpPck, tsa3000c01v1OutOrdIpPck, tsa3000c01v1FecRate, 
				tsa3000c01v1Link, tsa3000c01v1LinkTrapEnable, tsa3000c01v1BufferStatus, tsa3000c01v1PingStatus1, tsa3000c01v1SerialNo, 
				tsa3000c01v1SpeedForce, tsa3000c01v1BadCrcPck }
			STATUS current
			DESCRIPTION
				"Module TSA3000C01V1 Group"
			::= { varGroups 422601 }

		-- 1.3.6.1.4.1.10106.2.3.1.432201
		tle2001c01v1ModuleGroup OBJECT-GROUP
			OBJECTS {tle2001c01v1Index, tle2001c01v1Gpo1, tle2001c01v1Gpo2, tle2001c01v1Gpo3, tle2001c01v1Gpo4, 
				tle2001c01v1InvertGpi1Pol, tle2001c01v1InvertGpi2Pol, tle2001c01v1InvertGpi3Pol, tle2001c01v1InvertGpi4Pol, tle2001c01v1InvertGpo1Pol, 
				tle2001c01v1InvertGpo2Pol, tle2001c01v1InvertGpo3Pol, tle2001c01v1InvertGpo4Pol, tle2001c01v1Gpi1, tle2001c01v1Gpi1TrapEnable, 
				tle2001c01v1Gpi2, tle2001c01v1Gpi2TrapEnable, tle2001c01v1Gpi3, tle2001c01v1Gpi3TrapEnable, tle2001c01v1Gpi4, 
				tle2001c01v1Gpi4TrapEnable, tle2001c01v1RedBoard, tle2001c01v1RedBoardTrapEnable, tle2001c01v1EthLink, tle2001c01v1EthLinkTrapEnable, 
				tle2001c01v1EthRedAct, tle2001c01v1EthRedActTrapEnable, tle2001c01v1App1Ena, tle2001c01v1App2Ena, tle2001c01v1App3Ena, 
				tle2001c01v1App4Ena, tle2001c01v1App5Ena, tle2001c01v1App6Ena, tle2001c01v1App7Ena, tle2001c01v1App8Ena, 
				tle2001c01v1App9Ena, tle2001c01v1App10Ena, tle2001c01v1App11Ena, tle2001c01v1App12Ena, tle2001c01v1App13Ena, 
				tle2001c01v1App14Ena, tle2001c01v1App15Ena, tle2001c01v1App16Ena, tle2001c01v1SerialNo }
			STATUS current
			DESCRIPTION
				"Module TLE2001C01V1 Group"
			::= { varGroups 432201 }

		-- 1.3.6.1.4.1.10106.2.3.1.436601
		psu2000c02v1ModuleGroup OBJECT-GROUP
			OBJECTS {psu2000c02v1Index, psu2000c02v1PowerOff, psu2000c02v1PowerOffTrapEnable, psu2000c02v1TempWarning, psu2000c02v1TempWarningTrapEnable, 
				psu2000c02v1TempFail, psu2000c02v1TempFailTrapEnable, psu2000c02v1ActTemp, psu2000c02v1MeanTemp, psu2000c02v1MaxTemp, 
				psu2000c02v1PonHours, psu2000c02v1TotMaxTemp, psu2000c02v1TotPonHours, psu2000c02v1TotPonTimes, psu2000c02v1SerialNo }
			STATUS current
			DESCRIPTION
				"Module PSU2000C02V1 Group"
			::= { varGroups 436601 }

		-- 1.3.6.1.4.1.10106.2.3.1.437801
		eop2000c01v1ModuleGroup OBJECT-GROUP
			OBJECTS {eop2000c01v1Index, eop2000c01v1InputA, eop2000c01v1InputATrapEnable, eop2000c01v1InputB, eop2000c01v1InputBTrapEnable, 
				eop2000c01v1Mode, eop2000c01v1BckTxEn, eop2000c01v1UnlockA, eop2000c01v1UnlockATrapEnable, eop2000c01v1LFailA, 
				eop2000c01v1LFailATrapEnable, eop2000c01v1HdA, eop2000c01v1NoElecA, eop2000c01v1NoOpticA, eop2000c01v1UnlockB, 
				eop2000c01v1UnlockBTrapEnable, eop2000c01v1LFailB, eop2000c01v1LFailBTrapEnable, eop2000c01v1HdB, eop2000c01v1NoElecB, 
				eop2000c01v1NoOpticB, eop2000c01v1OpTxPres, eop2000c01v1OpTxPresTrapEnable, eop2000c01v1OpRxPres, eop2000c01v1OpRxPresTrapEnable, 
				eop2000c01v1SfpTxSn, eop2000c01v1SfpRxSn, eop2000c01v1SerialNo, eop2000c01v1RxPowerA, eop2000c01v1RxPowerB, 
				eop2000c01v1WavelengthA, eop2000c01v1WavelengthB }
			STATUS current
			DESCRIPTION
				"Module EOP2000C01V1 Group"
			::= { varGroups 437801 }

		-- 1.3.6.1.4.1.10106.2.3.1.438701
		avd2001c01v1ModuleGroup OBJECT-GROUP
			OBJECTS {avd2001c01v1Index, avd2001c01v1ClampEnable, avd2001c01v1ClampMode, avd2001c01v1LoopEnable, avd2001c01v1NoSigA, 
				avd2001c01v1NoSigATrapEnable, avd2001c01v1UnlockA, avd2001c01v1UnlockATrapEnable, avd2001c01v1SyncFormat, avd2001c01v1SyncFormatTrapEnable, 
				avd2001c01v1SerialNo }
			STATUS current
			DESCRIPTION
				"Module AVD2001C01V1 Group"
			::= { varGroups 438701 }

		-- 1.3.6.1.4.1.10106.2.3.1.442301
		hdc2000c01v1ModuleGroup OBJECT-GROUP
			OBJECTS {hdc2000c01v1Index, hdc2000c01v1ActivePreset, hdc2000c01v1LoadPreset, hdc2000c01v1SavePreset, hdc2000c01v1AnaRefFmt, 
				hdc2000c01v1AnaRefFmtTrapEnable, hdc2000c01v1GenlockMode, hdc2000c01v1EnaAud20Bit, hdc2000c01v1ModeConv, hdc2000c01v1ModeConvTrapEnable, 
				hdc2000c01v1OutAfd, hdc2000c01v1OutAfdTrapEnable, hdc2000c01v1OutCf, hdc2000c01v1OutCfTrapEnable, hdc2000c01v1InAfdExpct, 
				hdc2000c01v1InAfdExpctTrapEnable, hdc2000c01v1InCfExpct, hdc2000c01v1InCfExpctTrapEnable, hdc2000c01v1OutsdEnaS2016, hdc2000c01v1OutsdEnaVii, 
				hdc2000c01v1OutsdEnaWss, hdc2000c01v1OutsdEnaVitc, hdc2000c01v1OutsdEnaTxt, hdc2000c01v1SelAudPair0, hdc2000c01v1SelAudPair1, 
				hdc2000c01v1SelAudPair2, hdc2000c01v1SelAudPair3, hdc2000c01v1SelAudPair4, hdc2000c01v1SelAudPair5, hdc2000c01v1SelAudPair6, 
				hdc2000c01v1SelAudPair7, hdc2000c01v1VDelaySd, hdc2000c01v1HDelaySd, hdc2000c01v1Grp1P0Gain, hdc2000c01v1Grp1P0Phase, 
				hdc2000c01v1Grp1P1Gain, hdc2000c01v1Grp1P1Phase, hdc2000c01v1Grp2P0Gain, hdc2000c01v1Grp2P0Phase, hdc2000c01v1Grp2P1Gain, 
				hdc2000c01v1Grp2P1Phase, hdc2000c01v1Grp3P0Gain, hdc2000c01v1Grp3P0Phase, hdc2000c01v1Grp3P1Gain, hdc2000c01v1Grp3P1Phase, 
				hdc2000c01v1Grp4P0Gain, hdc2000c01v1Grp4P0Phase, hdc2000c01v1Grp4P1Gain, hdc2000c01v1Grp4P1Phase, hdc2000c01v1InAfdDetct, 
				hdc2000c01v1InAfdDetctTrapEnable, hdc2000c01v1InCfDetct, hdc2000c01v1InCfDetctTrapEnable, hdc2000c01v1InPhyFail, hdc2000c01v1InPhyFailTrapEnable, 
				hdc2000c01v1InFmtFail, hdc2000c01v1InFmtFailTrapEnable, hdc2000c01v1InIncFail, hdc2000c01v1InIncFailTrapEnable, hdc2000c01v1InPresCrcFail, 
				hdc2000c01v1InCrcFail, hdc2000c01v1InCrcFailTrapEnable, hdc2000c01v1InPrsS352Fail, hdc2000c01v1InS352Fail, hdc2000c01v1PresS2016Fail, 
				hdc2000c01v1ErrS2016Fail, hdc2000c01v1PresAudG1Fail, hdc2000c01v1PresAudG1FailTrapEnable, hdc2000c01v1PresAudG2Fail, hdc2000c01v1PresAudG2FailTrapEnable, 
				hdc2000c01v1PresAudG3Fail, hdc2000c01v1PresAudG3FailTrapEnable, hdc2000c01v1PresAudG4Fail, hdc2000c01v1PresAudG4FailTrapEnable, hdc2000c01v1RefFail, 
				hdc2000c01v1RefFailTrapEnable, hdc2000c01v1RefFmtFail, hdc2000c01v1RefFmtFailTrapEnable, hdc2000c01v1LockFail, hdc2000c01v1LockFailTrapEnable, 
				hdc2000c01v1AudPair0Fail, hdc2000c01v1AudPair0FailTrapEnable, hdc2000c01v1AudPair1Fail, hdc2000c01v1AudPair1FailTrapEnable, hdc2000c01v1AudPair2Fail, 
				hdc2000c01v1AudPair2FailTrapEnable, hdc2000c01v1AudPair3Fail, hdc2000c01v1AudPair3FailTrapEnable, hdc2000c01v1AudPair4Fail, hdc2000c01v1AudPair4FailTrapEnable, 
				hdc2000c01v1AudPair5Fail, hdc2000c01v1AudPair5FailTrapEnable, hdc2000c01v1AudPair6Fail, hdc2000c01v1AudPair6FailTrapEnable, hdc2000c01v1AudPair7Fail, 
				hdc2000c01v1AudPair7FailTrapEnable, hdc2000c01v1InFormat, hdc2000c01v1InFormatTrapEnable, hdc2000c01v1RefFormat, hdc2000c01v1RefFormatTrapEnable, 
				hdc2000c01v1MuteSd, hdc2000c01v1BlackSd, hdc2000c01v1SerialNo, hdc2000c01v1OutsdEnaCea608 }
			STATUS current
			DESCRIPTION
				"Module HDC2000C01V1 Group"
			::= { varGroups 442301 }

		-- 1.3.6.1.4.1.10106.2.3.1.442701
		gps3002c04v1ModuleGroup OBJECT-GROUP
			OBJECTS {gps3002c04v1Index, gps3002c04v1Holdover, gps3002c04v1RedundanceMode, gps3002c04v1RedundanceModeTrapEnable, gps3002c04v1CableDelay, 
				gps3002c04v1HoldoverStat, gps3002c04v1HoldoverStatTrapEnable, gps3002c04v1MaintenanceFail, gps3002c04v1MaintenanceFailTrapEnable, gps3002c04v1OutputsMuted, 
				gps3002c04v1OutputsMutedTrapEnable, gps3002c04v11ppsDisable, gps3002c04v11ppsDisableTrapEnable, gps3002c04v1AdquisitionStat, gps3002c04v1SatRxStat, 
				gps3002c04v1AntenaStat, gps3002c04v1AntenaStatTrapEnable, gps3002c04v1SatNoFail, gps3002c04v1GpsSiteSurv, gps3002c04v1GpsTrackSats, 
				gps3002c04v1GpsVisibleSats, gps3002c04v1GpsSignalLevel, gps3002c04v1HoldoverTime, gps3002c04v1FreqDriftEst, gps3002c04v1PhaseDriftEst, 
				gps3002c04v1SerialNo }
			STATUS current
			DESCRIPTION
				"Module GPS3002C04V1 Group"
			::= { varGroups 442701 }

		-- 1.3.6.1.4.1.10106.2.3.1.443601
		cws2016c01v1ModuleGroup OBJECT-GROUP
			OBJECTS {cws2016c01v1Index, cws2016c01v1SerialNo }
			STATUS current
			DESCRIPTION
				"Module CWS2016C01V1 Group"
			::= { varGroups 443601 }

		-- 1.3.6.1.4.1.10106.2.3.1.445101
		hdc2000c02v1ModuleGroup OBJECT-GROUP
			OBJECTS {hdc2000c02v1Index, hdc2000c02v1ActivePreset, hdc2000c02v1LoadPreset, hdc2000c02v1SavePreset, hdc2000c02v1AnaRefFmt, 
				hdc2000c02v1AnaRefFmtTrapEnable, hdc2000c02v1GenlockMode, hdc2000c02v1EnaAud20Bit, hdc2000c02v1ModeConv, hdc2000c02v1ModeConvTrapEnable, 
				hdc2000c02v1OutAfd, hdc2000c02v1OutAfdTrapEnable, hdc2000c02v1OutCf, hdc2000c02v1OutCfTrapEnable, hdc2000c02v1InAfdExpct, 
				hdc2000c02v1InAfdExpctTrapEnable, hdc2000c02v1InCfExpct, hdc2000c02v1InCfExpctTrapEnable, hdc2000c02v1OutsdEnaS2016, hdc2000c02v1OutsdEnaVii, 
				hdc2000c02v1OutsdEnaWss, hdc2000c02v1OutsdEnaVitc, hdc2000c02v1OutsdEnaTxt, hdc2000c02v1SelAudPair0, hdc2000c02v1SelAudPair1, 
				hdc2000c02v1SelAudPair2, hdc2000c02v1SelAudPair3, hdc2000c02v1SelAudPair4, hdc2000c02v1SelAudPair5, hdc2000c02v1SelAudPair6, 
				hdc2000c02v1SelAudPair7, hdc2000c02v1ChromaDis, hdc2000c02v1LumaFilter, hdc2000c02v1VbiBlank, hdc2000c02v1VDelaySd, 
				hdc2000c02v1HDelaySd, hdc2000c02v1Grp1P0Gain, hdc2000c02v1Grp1P0Phase, hdc2000c02v1Grp1P1Gain, hdc2000c02v1Grp1P1Phase, 
				hdc2000c02v1Grp2P0Gain, hdc2000c02v1Grp2P0Phase, hdc2000c02v1Grp2P1Gain, hdc2000c02v1Grp2P1Phase, hdc2000c02v1Grp3P0Gain, 
				hdc2000c02v1Grp3P0Phase, hdc2000c02v1Grp3P1Gain, hdc2000c02v1Grp3P1Phase, hdc2000c02v1Grp4P0Gain, hdc2000c02v1Grp4P0Phase, 
				hdc2000c02v1Grp4P1Gain, hdc2000c02v1Grp4P1Phase, hdc2000c02v1InAfdDetct, hdc2000c02v1InAfdDetctTrapEnable, hdc2000c02v1InCfDetct, 
				hdc2000c02v1InCfDetctTrapEnable, hdc2000c02v1InPhyFail, hdc2000c02v1InPhyFailTrapEnable, hdc2000c02v1InFmtFail, hdc2000c02v1InFmtFailTrapEnable, 
				hdc2000c02v1InIncFail, hdc2000c02v1InIncFailTrapEnable, hdc2000c02v1InPresCrcFail, hdc2000c02v1InCrcFail, hdc2000c02v1InCrcFailTrapEnable, 
				hdc2000c02v1InPrsS352Fail, hdc2000c02v1InS352Fail, hdc2000c02v1PresS2016Fail, hdc2000c02v1ErrS2016Fail, hdc2000c02v1PresAudG1Fail, 
				hdc2000c02v1PresAudG1FailTrapEnable, hdc2000c02v1PresAudG2Fail, hdc2000c02v1PresAudG2FailTrapEnable, hdc2000c02v1PresAudG3Fail, hdc2000c02v1PresAudG3FailTrapEnable, 
				hdc2000c02v1PresAudG4Fail, hdc2000c02v1PresAudG4FailTrapEnable, hdc2000c02v1RefFail, hdc2000c02v1RefFailTrapEnable, hdc2000c02v1RefFmtFail, 
				hdc2000c02v1RefFmtFailTrapEnable, hdc2000c02v1LockFail, hdc2000c02v1LockFailTrapEnable, hdc2000c02v1AudPair0Fail, hdc2000c02v1AudPair0FailTrapEnable, 
				hdc2000c02v1AudPair1Fail, hdc2000c02v1AudPair1FailTrapEnable, hdc2000c02v1AudPair2Fail, hdc2000c02v1AudPair2FailTrapEnable, hdc2000c02v1AudPair3Fail, 
				hdc2000c02v1AudPair3FailTrapEnable, hdc2000c02v1AudPair4Fail, hdc2000c02v1AudPair4FailTrapEnable, hdc2000c02v1AudPair5Fail, hdc2000c02v1AudPair5FailTrapEnable, 
				hdc2000c02v1AudPair6Fail, hdc2000c02v1AudPair6FailTrapEnable, hdc2000c02v1AudPair7Fail, hdc2000c02v1AudPair7FailTrapEnable, hdc2000c02v1InFormat, 
				hdc2000c02v1InFormatTrapEnable, hdc2000c02v1RefFormat, hdc2000c02v1RefFormatTrapEnable, hdc2000c02v1MuteSd, hdc2000c02v1BlackSd, 
				hdc2000c02v1SerialNo, hdc2000c02v1OutsdEnaCea608 }
			STATUS current
			DESCRIPTION
				"Module HDC2000C02V1 Group"
			::= { varGroups 445101 }

		-- 1.3.6.1.4.1.10106.2.3.1.446901
		hxc3000c01v1ModuleGroup OBJECT-GROUP
			OBJECTS {hxc3000c01v1Index, hxc3000c01v1ActivePreset, hxc3000c01v1LoadPreset, hxc3000c01v1SavePreset, hxc3000c01v1AnaRefFmt, 
				hxc3000c01v1AnaRefFmtTrapEnable, hxc3000c01v1GenlockMode, hxc3000c01v1EnaAud20Bit, hxc3000c01v1FailMode, hxc3000c01v1ModeConv, 
				hxc3000c01v1ModeConvTrapEnable, hxc3000c01v1OutAfd, hxc3000c01v1OutAfdTrapEnable, hxc3000c01v1OutCf, hxc3000c01v1OutCfTrapEnable, 
				hxc3000c01v1Esc11, hxc3000c01v1InAfdExpct, hxc3000c01v1InAfdExpctTrapEnable, hxc3000c01v1InCfExpct, hxc3000c01v1InCfExpctTrapEnable, 
				hxc3000c01v1TxFmt, hxc3000c01v1TxFmtTrapEnable, hxc3000c01v1DeintAlgorithm, hxc3000c01v1DeintAlgorithmTrapEnable, hxc3000c01v1OutEnaS2016, 
				hxc3000c01v1OutEnaVii, hxc3000c01v1OutEnaWss, hxc3000c01v1OutEnaVitc, hxc3000c01v1OutEnaAtc, hxc3000c01v1OutEnaTxt, 
				hxc3000c01v1OutEnaCea608, hxc3000c01v1SelAudPair0, hxc3000c01v1SelAudPair1, hxc3000c01v1SelAudPair2, hxc3000c01v1SelAudPair3, 
				hxc3000c01v1SelAudPair4, hxc3000c01v1SelAudPair5, hxc3000c01v1SelAudPair6, hxc3000c01v1SelAudPair7, hxc3000c01v1VDelay, 
				hxc3000c01v1HDelay, hxc3000c01v1Grp1P0Gain, hxc3000c01v1Grp1P0Phase, hxc3000c01v1Grp1P1Gain, hxc3000c01v1Grp1P1Phase, 
				hxc3000c01v1Grp2P0Gain, hxc3000c01v1Grp2P0Phase, hxc3000c01v1Grp2P1Gain, hxc3000c01v1Grp2P1Phase, hxc3000c01v1Grp3P0Gain, 
				hxc3000c01v1Grp3P0Phase, hxc3000c01v1Grp3P1Gain, hxc3000c01v1Grp3P1Phase, hxc3000c01v1Grp4P0Gain, hxc3000c01v1Grp4P0Phase, 
				hxc3000c01v1Grp4P1Gain, hxc3000c01v1Grp4P1Phase, hxc3000c01v1StatFlash, hxc3000c01v1InPhyFail, hxc3000c01v1InPhyFailTrapEnable, 
				hxc3000c01v1InFmtFail, hxc3000c01v1InFmtFailTrapEnable, hxc3000c01v1InIncFail, hxc3000c01v1InIncFailTrapEnable, hxc3000c01v1InPresCrcFail, 
				hxc3000c01v1InCrcFail, hxc3000c01v1InCrcFailTrapEnable, hxc3000c01v1InPrsS352Fail, hxc3000c01v1InS352Fail, hxc3000c01v1PresS2016Fail, 
				hxc3000c01v1ErrS2016Fail, hxc3000c01v1PresAudG1Fail, hxc3000c01v1PresAudG1FailTrapEnable, hxc3000c01v1PresAudG2Fail, hxc3000c01v1PresAudG2FailTrapEnable, 
				hxc3000c01v1PresAudG3Fail, hxc3000c01v1PresAudG3FailTrapEnable, hxc3000c01v1PresAudG4Fail, hxc3000c01v1PresAudG4FailTrapEnable, hxc3000c01v1RefFail, 
				hxc3000c01v1RefFailTrapEnable, hxc3000c01v1RefFmtFail, hxc3000c01v1RefFmtFailTrapEnable, hxc3000c01v1LockFail, hxc3000c01v1LockFailTrapEnable, 
				hxc3000c01v1AudPair0Fail, hxc3000c01v1AudPair0FailTrapEnable, hxc3000c01v1AudPair1Fail, hxc3000c01v1AudPair1FailTrapEnable, hxc3000c01v1AudPair2Fail, 
				hxc3000c01v1AudPair2FailTrapEnable, hxc3000c01v1AudPair3Fail, hxc3000c01v1AudPair3FailTrapEnable, hxc3000c01v1AudPair4Fail, hxc3000c01v1AudPair4FailTrapEnable, 
				hxc3000c01v1AudPair5Fail, hxc3000c01v1AudPair5FailTrapEnable, hxc3000c01v1AudPair6Fail, hxc3000c01v1AudPair6FailTrapEnable, hxc3000c01v1AudPair7Fail, 
				hxc3000c01v1AudPair7FailTrapEnable, hxc3000c01v1InAfdDetct, hxc3000c01v1InAfdDetctTrapEnable, hxc3000c01v1InCfDetct, hxc3000c01v1InCfDetctTrapEnable, 
				hxc3000c01v1InFormat, hxc3000c01v1InFormatTrapEnable, hxc3000c01v1RefFormat, hxc3000c01v1RefFormatTrapEnable, hxc3000c01v1TxFormat, 
				hxc3000c01v1TxFormatTrapEnable, hxc3000c01v1TxtPres, hxc3000c01v1VitcPres, hxc3000c01v1Mute, hxc3000c01v1Black, 
				hxc3000c01v1Gpi1, hxc3000c01v1Gpi2, hxc3000c01v1Gpi3, hxc3000c01v1Gpi4, hxc3000c01v1SerialNo, 
				hxc3000c01v1MuteEna }
			STATUS current
			DESCRIPTION
				"Module HXC3000C01V1 Group"
			::= { varGroups 446901 }

		-- 1.3.6.1.4.1.10106.2.3.1.454401
		hsw2000c01v1ModuleGroup OBJECT-GROUP
			OBJECTS {hsw2000c01v1Index, hsw2000c01v1ActivePreset, hsw2000c01v1LoadPreset, hsw2000c01v1SavePreset, hsw2000c01v1StateSel, 
				hsw2000c01v1StateSelTrapEnable, hsw2000c01v1SwitchMode, hsw2000c01v1SwitchModeTrapEnable, hsw2000c01v1FreezeMode, hsw2000c01v1BypassEnable, 
				hsw2000c01v1BypassEnableTrapEnable, hsw2000c01v1InpFailMode, hsw2000c01v1StateAMap, hsw2000c01v1StateBMap, hsw2000c01v1AnaRefFmt, 
				hsw2000c01v1In1StChange, hsw2000c01v1In2StChange, hsw2000c01v1InputChange, hsw2000c01v1DePer2IncIn1, hsw2000c01v1DePer2IncIn2, 
				hsw2000c01v1VDelay, hsw2000c01v1HDelay, hsw2000c01v1Holdoff, hsw2000c01v1PhyFailTim, hsw2000c01v1FmtFailTim, 
				hsw2000c01v1IncFailTim, hsw2000c01v1StatusMode, hsw2000c01v1SynchroModeIn1, hsw2000c01v1SynchroModeIn2, hsw2000c01v1BlkFailTim, 
				hsw2000c01v1FrzFailTim, hsw2000c01v1PatFailTim, hsw2000c01v1CrcFailTim, hsw2000c01v1SilFailTim, hsw2000c01v1OvrFailTim, 
				hsw2000c01v1PhFailTim, hsw2000c01v1PresFailTim, hsw2000c01v1ActPer1, hsw2000c01v1DeactPer1, hsw2000c01v1ActPer2, 
				hsw2000c01v1DeactPer2, hsw2000c01v1CrcThreshold, hsw2000c01v1BlackThreshold, hsw2000c01v1VertFrozenWin, hsw2000c01v1HtalFrozenWin, 
				hsw2000c01v1In1PhyFailMsk, hsw2000c01v1In1FmtFailMsk, hsw2000c01v1In1IncFailMsk, hsw2000c01v1In1BlkFailMsk, hsw2000c01v1In1FrzFailMsk, 
				hsw2000c01v1In1PatFailMsk, hsw2000c01v1In1CrcFailMsk, hsw2000c01v1In1SilFailMsk, hsw2000c01v1In1OvrFailMsk, hsw2000c01v1In1PhFailMsk, 
				hsw2000c01v1In1PreFailMsk, hsw2000c01v1In2PhyFailMsk, hsw2000c01v1In2FmtFailMsk, hsw2000c01v1In2IncFailMsk, hsw2000c01v1In2BlkFailMsk, 
				hsw2000c01v1In2FrzFailMsk, hsw2000c01v1In2PatFailMsk, hsw2000c01v1In2CrcFailMsk, hsw2000c01v1In2SilFailMsk, hsw2000c01v1In2OvrFailMsk, 
				hsw2000c01v1In2PhFailMsk, hsw2000c01v1In2PreFailMsk, hsw2000c01v1RefFailMsk, hsw2000c01v1LockFailMsk, hsw2000c01v1In1AudG1p0Msk, 
				hsw2000c01v1In1AudG1p1Msk, hsw2000c01v1In1AudG2p0Msk, hsw2000c01v1In1AudG2p1Msk, hsw2000c01v1In1AudG3p0Msk, hsw2000c01v1In1AudG3p1Msk, 
				hsw2000c01v1In1AudG4p0Msk, hsw2000c01v1In1AudG4p1Msk, hsw2000c01v1In2AudG1p0Msk, hsw2000c01v1In2AudG1p1Msk, hsw2000c01v1In2AudG2p0Msk, 
				hsw2000c01v1In2AudG2p1Msk, hsw2000c01v1In2AudG3p0Msk, hsw2000c01v1In2AudG3p1Msk, hsw2000c01v1In2AudG4p0Msk, hsw2000c01v1In2AudG4p1Msk, 
				hsw2000c01v1FrzToBckTime, hsw2000c01v1SilenceLevel, hsw2000c01v1SilenceTime, hsw2000c01v1OverloadLevel, hsw2000c01v1TxtLinesThrs, 
				hsw2000c01v1In1Fail, hsw2000c01v1In1FailTrapEnable, hsw2000c01v1In2Fail, hsw2000c01v1In2FailTrapEnable, hsw2000c01v1EqualPid, 
				hsw2000c01v1EqualPidTrapEnable, hsw2000c01v1SelOut1, hsw2000c01v1SelOut1TrapEnable, hsw2000c01v1SelOut2, hsw2000c01v1SelOut2TrapEnable, 
				hsw2000c01v1EqualUmid, hsw2000c01v1EqualUmidTrapEnable, hsw2000c01v1In1PhyFail, hsw2000c01v1In1PhyFailTrapEnable, hsw2000c01v1In1FmtFail, 
				hsw2000c01v1In1FmtFailTrapEnable, hsw2000c01v1In1IncFail, hsw2000c01v1In1IncFailTrapEnable, hsw2000c01v1In1BlkFail, hsw2000c01v1In1BlkFailTrapEnable, 
				hsw2000c01v1In1FrzFail, hsw2000c01v1In1FrzFailTrapEnable, hsw2000c01v1In1PatFail, hsw2000c01v1In1PatFailTrapEnable, hsw2000c01v1In1CrcFail, 
				hsw2000c01v1In1CrcFailTrapEnable, hsw2000c01v1In1SilFail, hsw2000c01v1In1SilFailTrapEnable, hsw2000c01v1In1OvrFail, hsw2000c01v1In1OvrFailTrapEnable, 
				hsw2000c01v1In1PhFail, hsw2000c01v1In1PhFailTrapEnable, hsw2000c01v1In1PreFail, hsw2000c01v1In1PreFailTrapEnable, hsw2000c01v1In2PhyFail, 
				hsw2000c01v1In2PhyFailTrapEnable, hsw2000c01v1In2FmtFail, hsw2000c01v1In2FmtFailTrapEnable, hsw2000c01v1In2IncFail, hsw2000c01v1In2IncFailTrapEnable, 
				hsw2000c01v1In2BlkFail, hsw2000c01v1In2BlkFailTrapEnable, hsw2000c01v1In2FrzFail, hsw2000c01v1In2FrzFailTrapEnable, hsw2000c01v1In2PatFail, 
				hsw2000c01v1In2PatFailTrapEnable, hsw2000c01v1In2CrcFail, hsw2000c01v1In2CrcFailTrapEnable, hsw2000c01v1In2SilFail, hsw2000c01v1In2SilFailTrapEnable, 
				hsw2000c01v1In2OvrFail, hsw2000c01v1In2OvrFailTrapEnable, hsw2000c01v1In2PhFail, hsw2000c01v1In2PhFailTrapEnable, hsw2000c01v1In2PreFail, 
				hsw2000c01v1In2PreFailTrapEnable, hsw2000c01v1RefFail, hsw2000c01v1RefFailTrapEnable, hsw2000c01v1LockFail, hsw2000c01v1LockFailTrapEnable, 
				hsw2000c01v1In1Format, hsw2000c01v1In1FormatTrapEnable, hsw2000c01v1In2Format, hsw2000c01v1In2FormatTrapEnable, hsw2000c01v1RefFormat, 
				hsw2000c01v1RefFormatTrapEnable, hsw2000c01v1In1PidPres, hsw2000c01v1In2PidPres, hsw2000c01v1In1UmidPres, hsw2000c01v1In2UmidPres, 
				hsw2000c01v1In1Grp1Pres, hsw2000c01v1In1Grp1PresTrapEnable, hsw2000c01v1In1Grp2Pres, hsw2000c01v1In1Grp2PresTrapEnable, hsw2000c01v1In1Grp3Pres, 
				hsw2000c01v1In1Grp3PresTrapEnable, hsw2000c01v1In1Grp4Pres, hsw2000c01v1In1Grp4PresTrapEnable, hsw2000c01v1In1Grp1P0Stat, hsw2000c01v1In1Grp1P0StatTrapEnable, 
				hsw2000c01v1In1Grp1P1Stat, hsw2000c01v1In1Grp1P1StatTrapEnable, hsw2000c01v1In1Grp2P0Stat, hsw2000c01v1In1Grp2P0StatTrapEnable, hsw2000c01v1In1Grp2P1Stat, 
				hsw2000c01v1In1Grp2P1StatTrapEnable, hsw2000c01v1In1Grp3P0Stat, hsw2000c01v1In1Grp3P0StatTrapEnable, hsw2000c01v1In1Grp3P1Stat, hsw2000c01v1In1Grp3P1StatTrapEnable, 
				hsw2000c01v1In1Grp4P0Stat, hsw2000c01v1In1Grp4P0StatTrapEnable, hsw2000c01v1In1Grp4P1Stat, hsw2000c01v1In1Grp4P1StatTrapEnable, hsw2000c01v1In2Grp1Pres, 
				hsw2000c01v1In2Grp1PresTrapEnable, hsw2000c01v1In2Grp2Pres, hsw2000c01v1In2Grp2PresTrapEnable, hsw2000c01v1In2Grp3Pres, hsw2000c01v1In2Grp3PresTrapEnable, 
				hsw2000c01v1In2Grp4Pres, hsw2000c01v1In2Grp4PresTrapEnable, hsw2000c01v1In2Grp1P0Stat, hsw2000c01v1In2Grp1P0StatTrapEnable, hsw2000c01v1In2Grp1P1Stat, 
				hsw2000c01v1In2Grp1P1StatTrapEnable, hsw2000c01v1In2Grp2P0Stat, hsw2000c01v1In2Grp2P0StatTrapEnable, hsw2000c01v1In2Grp2P1Stat, hsw2000c01v1In2Grp2P1StatTrapEnable, 
				hsw2000c01v1In2Grp3P0Stat, hsw2000c01v1In2Grp3P0StatTrapEnable, hsw2000c01v1In2Grp3P1Stat, hsw2000c01v1In2Grp3P1StatTrapEnable, hsw2000c01v1In2Grp4P0Stat, 
				hsw2000c01v1In2Grp4P0StatTrapEnable, hsw2000c01v1In2Grp4P1Stat, hsw2000c01v1In2Grp4P1StatTrapEnable, hsw2000c01v1In1WssCod, hsw2000c01v1In1WssCodTrapEnable, 
				hsw2000c01v1In1WssStat, hsw2000c01v1In1WssStatTrapEnable, hsw2000c01v1In1ViiAfdCod, hsw2000c01v1In1ViiAfdCodTrapEnable, hsw2000c01v1In1ViiStat, 
				hsw2000c01v1In1ViiStatTrapEnable, hsw2000c01v1In12016AfdCod, hsw2000c01v1In12016AfdCodTrapEnable, hsw2000c01v1In12016Stat, hsw2000c01v1In12016StatTrapEnable, 
				hsw2000c01v1In2WssCod, hsw2000c01v1In2WssCodTrapEnable, hsw2000c01v1In2WssStat, hsw2000c01v1In2WssStatTrapEnable, hsw2000c01v1In2ViiAfdCod, 
				hsw2000c01v1In2ViiAfdCodTrapEnable, hsw2000c01v1In2ViiStat, hsw2000c01v1In2ViiStatTrapEnable, hsw2000c01v1In22016Cod, hsw2000c01v1In22016CodTrapEnable, 
				hsw2000c01v1In22016Stat, hsw2000c01v1In22016StatTrapEnable, hsw2000c01v1In1TxtLinLow, hsw2000c01v1In1TxtLinLowTrapEnable, hsw2000c01v1In1TxtLin1s, 
				hsw2000c01v1In2TxtLinLow, hsw2000c01v1In2TxtLinLowTrapEnable, hsw2000c01v1In2TxtLin1s, hsw2000c01v1SerialNo }
			STATUS current
			DESCRIPTION
				"Module HSW2000C01V1 Group"
			::= { varGroups 454401 }

		-- 1.3.6.1.4.1.10106.2.3.1.454501
		htg2000c01v1ModuleGroup OBJECT-GROUP
			OBJECTS {htg2000c01v1Index, htg2000c01v1ActivePreset, htg2000c01v1LoadPreset, htg2000c01v1SavePreset, htg2000c01v1ExpRefFormat, 
				htg2000c01v1ExpRefFormatTrapEnable, htg2000c01v1RefInput, htg2000c01v1RefInputTrapEnable, htg2000c01v1MeasInput, htg2000c01v1OutFormat1, 
				htg2000c01v1OutFormat1TrapEnable, htg2000c01v1OutMute1, htg2000c01v1HDelay1, htg2000c01v1VDelay1, htg2000c01v1TestSignal1, 
				htg2000c01v1EnGrp1Aud1, htg2000c01v1EnGrp2Aud1, htg2000c01v1EnGrp3Aud1, htg2000c01v1EnGrp4Aud1, htg2000c01v1EnOsd1, 
				htg2000c01v1AudFrP0G01, htg2000c01v1AudFrP1G01, htg2000c01v1AudFrP0G11, htg2000c01v1AudFrP1G11, htg2000c01v1AudFrP0G21, 
				htg2000c01v1AudFrP1G21, htg2000c01v1AudFrP0G31, htg2000c01v1AudFrP1G31, htg2000c01v1AudDipP0G01, htg2000c01v1AudDipP1G01, 
				htg2000c01v1AudDipP0G11, htg2000c01v1AudDipP1G11, htg2000c01v1AudDipP0G21, htg2000c01v1AudDipP1G21, htg2000c01v1AudDipP0G31, 
				htg2000c01v1AudDipP1G31, htg2000c01v1AudLevP0G01, htg2000c01v1AudLevP0G11, htg2000c01v1AudLevP1G01, htg2000c01v1AudLevP1G11, 
				htg2000c01v1AudLevP0G21, htg2000c01v1AudLevP1G21, htg2000c01v1AudLevP0G31, htg2000c01v1AudLevP1G31, htg2000c01v1OutFormat2, 
				htg2000c01v1OutFormat2TrapEnable, htg2000c01v1OutMute2, htg2000c01v1HDelay2, htg2000c01v1VDelay2, htg2000c01v1TestSignal2, 
				htg2000c01v1EnGrp1Aud2, htg2000c01v1EnGrp2Aud2, htg2000c01v1EnGrp3Aud2, htg2000c01v1EnGrp4Aud2, htg2000c01v1EnOsd2, 
				htg2000c01v1AudFrP0G02, htg2000c01v1AudFrP1G02, htg2000c01v1AudFrP0G12, htg2000c01v1AudFrP1G12, htg2000c01v1AudFrP0G22, 
				htg2000c01v1AudFrP1G22, htg2000c01v1AudFrP0G32, htg2000c01v1AudFrP1G32, htg2000c01v1AudDipP0G02, htg2000c01v1AudDipP1G02, 
				htg2000c01v1AudDipP0G12, htg2000c01v1AudDipP1G12, htg2000c01v1AudDipP0G22, htg2000c01v1AudDipP1G22, htg2000c01v1AudDipP0G32, 
				htg2000c01v1AudDipP1G32, htg2000c01v1AudLevP0G02, htg2000c01v1AudLevP0G12, htg2000c01v1AudLevP1G02, htg2000c01v1AudLevP1G12, 
				htg2000c01v1AudLevP0G22, htg2000c01v1AudLevP1G22, htg2000c01v1AudLevP0G32, htg2000c01v1AudLevP1G32, htg2000c01v1OutFormat3, 
				htg2000c01v1OutFormat3TrapEnable, htg2000c01v1HDelay3, htg2000c01v1VDelay3, htg2000c01v1Sch3, htg2000c01v1ArefFailMsk, 
				htg2000c01v1DrefFailMsk, htg2000c01v1IrefFailMsk, htg2000c01v1RefIncFailMsk, htg2000c01v1RefLckFailMsk, htg2000c01v1ArefFail, 
				htg2000c01v1ArefFailTrapEnable, htg2000c01v1DrefFail, htg2000c01v1DrefFailTrapEnable, htg2000c01v1IrefFail, htg2000c01v1IrefFailTrapEnable, 
				htg2000c01v1RefIncFail, htg2000c01v1RefIncFailTrapEnable, htg2000c01v1RefLockFail, htg2000c01v1RefLockFailTrapEnable, htg2000c01v1DrefCrcFail, 
				htg2000c01v1DrefCrcFailTrapEnable, htg2000c01v1ArefFormat, htg2000c01v1ArefFormatTrapEnable, htg2000c01v1DrefFormat, htg2000c01v1DrefFormatTrapEnable, 
				htg2000c01v1MeasDelay, htg2000c01v1MeasFreq, htg2000c01v1SerialNo }
			STATUS current
			DESCRIPTION
				"Module HTG2000C01V1 Group"
			::= { varGroups 454501 }

		-- 1.3.6.1.4.1.10106.2.3.1.454502
		htg2000c01v2ModuleGroup OBJECT-GROUP
			OBJECTS {htg2000c01v2Index, htg2000c01v2ActivePreset, htg2000c01v2LoadPreset, htg2000c01v2SavePreset, htg2000c01v2ExpRefFormat, 
				htg2000c01v2ExpRefFormatTrapEnable, htg2000c01v2RefInput, htg2000c01v2RefInputTrapEnable, htg2000c01v2MeasInput, htg2000c01v2OutFormat1, 
				htg2000c01v2OutFormat1TrapEnable, htg2000c01v2OutMute1, htg2000c01v2HDelay1, htg2000c01v2VDelay1, htg2000c01v2TestSignal1, 
				htg2000c01v2EnGrp1Aud1, htg2000c01v2EnGrp2Aud1, htg2000c01v2EnGrp3Aud1, htg2000c01v2EnGrp4Aud1, htg2000c01v2EnOsd1, 
				htg2000c01v2AudFrP0G01, htg2000c01v2AudFrP1G01, htg2000c01v2AudFrP0G11, htg2000c01v2AudFrP1G11, htg2000c01v2AudFrP0G21, 
				htg2000c01v2AudFrP1G21, htg2000c01v2AudFrP0G31, htg2000c01v2AudFrP1G31, htg2000c01v2AudDipP0G01, htg2000c01v2AudDipP1G01, 
				htg2000c01v2AudDipP0G11, htg2000c01v2AudDipP1G11, htg2000c01v2AudDipP0G21, htg2000c01v2AudDipP1G21, htg2000c01v2AudDipP0G31, 
				htg2000c01v2AudDipP1G31, htg2000c01v2AudLevP0G01, htg2000c01v2AudLevP0G11, htg2000c01v2AudLevP1G01, htg2000c01v2AudLevP1G11, 
				htg2000c01v2AudLevP0G21, htg2000c01v2AudLevP1G21, htg2000c01v2AudLevP0G31, htg2000c01v2AudLevP1G31, htg2000c01v2OutFormat2, 
				htg2000c01v2OutFormat2TrapEnable, htg2000c01v2OutMute2, htg2000c01v2HDelay2, htg2000c01v2VDelay2, htg2000c01v2TestSignal2, 
				htg2000c01v2EnGrp1Aud2, htg2000c01v2EnGrp2Aud2, htg2000c01v2EnGrp3Aud2, htg2000c01v2EnGrp4Aud2, htg2000c01v2EnOsd2, 
				htg2000c01v2AudFrP0G02, htg2000c01v2AudFrP1G02, htg2000c01v2AudFrP0G12, htg2000c01v2AudFrP1G12, htg2000c01v2AudFrP0G22, 
				htg2000c01v2AudFrP1G22, htg2000c01v2AudFrP0G32, htg2000c01v2AudFrP1G32, htg2000c01v2AudDipP0G02, htg2000c01v2AudDipP1G02, 
				htg2000c01v2AudDipP0G12, htg2000c01v2AudDipP1G12, htg2000c01v2AudDipP0G22, htg2000c01v2AudDipP1G22, htg2000c01v2AudDipP0G32, 
				htg2000c01v2AudDipP1G32, htg2000c01v2AudLevP0G02, htg2000c01v2AudLevP0G12, htg2000c01v2AudLevP1G02, htg2000c01v2AudLevP1G12, 
				htg2000c01v2AudLevP0G22, htg2000c01v2AudLevP1G22, htg2000c01v2AudLevP0G32, htg2000c01v2AudLevP1G32, htg2000c01v2OutFormat3, 
				htg2000c01v2OutFormat3TrapEnable, htg2000c01v2HDelay3, htg2000c01v2VDelay3, htg2000c01v2Sch3, htg2000c01v2ArefFailMsk, 
				htg2000c01v2DrefFailMsk, htg2000c01v2IrefFailMsk, htg2000c01v2RefIncFailMsk, htg2000c01v2RefLckFailMsk, htg2000c01v2SumMonthSt, 
				htg2000c01v2SumWeekSt, htg2000c01v2SumWDaySt, htg2000c01v2SumHourSt, htg2000c01v2SumHourOffset, htg2000c01v2WinMonthSt, 
				htg2000c01v2WinWeekSt, htg2000c01v2WinWDaySt, htg2000c01v2WinHourSt, htg2000c01v2WinHourOffset, htg2000c01v2EnDlsave, 
				htg2000c01v2DropFrame, htg2000c01v2Bgf, htg2000c01v2DateFormat, htg2000c01v2EnDateGen, htg2000c01v2AdjHourDay, 
				htg2000c01v2En1001secRst, htg2000c01v2ArefFail, htg2000c01v2ArefFailTrapEnable, htg2000c01v2DrefFail, htg2000c01v2DrefFailTrapEnable, 
				htg2000c01v2IrefFail, htg2000c01v2IrefFailTrapEnable, htg2000c01v2RefIncFail, htg2000c01v2RefIncFailTrapEnable, htg2000c01v2RefLockFail, 
				htg2000c01v2RefLockFailTrapEnable, htg2000c01v2DrefCrcFail, htg2000c01v2DrefCrcFailTrapEnable, htg2000c01v2TcFail, htg2000c01v2ArefFormat, 
				htg2000c01v2ArefFormatTrapEnable, htg2000c01v2DrefFormat, htg2000c01v2DrefFormatTrapEnable, htg2000c01v2MeasDelay, htg2000c01v2MeasFreq, 
				htg2000c01v2SerialNo, htg2000c01v2VidDip1, htg2000c01v2VidDip2, htg2000c01v2OsdDly1, htg2000c01v2OsdDly2, 
				htg2000c01v2AvDlyBlack, htg2000c01v2AvDlySil, htg2000c01v2DelayG1p0l, htg2000c01v2DelayG1p0r, htg2000c01v2DelayG1p1l, 
				htg2000c01v2DelayG1p1r, htg2000c01v2DelayG2p0l, htg2000c01v2DelayG2p0r, htg2000c01v2DelayG2p1l, htg2000c01v2DelayG2p1r, 
				htg2000c01v2DelayG3p0l, htg2000c01v2DelayG3p0r, htg2000c01v2DelayG3p1l, htg2000c01v2DelayG3p1r, htg2000c01v2DelayG4p0l, 
				htg2000c01v2DelayG4p0r, htg2000c01v2DelayG4p1l, htg2000c01v2DelayG4p1r, htg2000c01v2AvSeqG1p0, htg2000c01v2AvSeqG1p1, 
				htg2000c01v2AvSeqG2p0, htg2000c01v2AvSeqG2p1, htg2000c01v2AvSeqG3p0, htg2000c01v2AvSeqG3p1, htg2000c01v2AvSeqG4p0, 
				htg2000c01v2AvSeqG4p1, htg2000c01v2AudGrpPres1, htg2000c01v2AudGrpPres2, htg2000c01v2AudGrpPres3, htg2000c01v2AudGrpPres4, 
				htg2000c01v2AvSeqPhase }
			STATUS current
			DESCRIPTION
				"Module HTG2000C01V2 Group"
			::= { varGroups 454502 }

		-- 1.3.6.1.4.1.10106.2.3.1.456201
		aad2000c01v1ModuleGroup OBJECT-GROUP
			OBJECTS {aad2000c01v1Index, aad2000c01v1Input, aad2000c01v1BckTxEn, aad2000c01v1LedMode, aad2000c01v1Vu8dbu, 
				aad2000c01v1OvlThrLevel, aad2000c01v1SilThrLevel, aad2000c01v1NoSigTout, aad2000c01v1Silence, aad2000c01v1SilenceTrapEnable, 
				aad2000c01v1Overload, aad2000c01v1OverloadTrapEnable, aad2000c01v1VuLevel, aad2000c01v1PkLevel, aad2000c01v1SerialNo }
			STATUS current
			DESCRIPTION
				"Module AAD2000C01V1 Group"
			::= { varGroups 456201 }

		-- 1.3.6.1.4.1.10106.2.3.1.460201
		aad2000c02v1ModuleGroup OBJECT-GROUP
			OBJECTS {aad2000c02v1Index, aad2000c02v1Input, aad2000c02v1BckTxEn, aad2000c02v1LedMode, aad2000c02v1Vu8dbu, 
				aad2000c02v1OvlThrLevel, aad2000c02v1SilThrLevel, aad2000c02v1NoSigTout, aad2000c02v1Silence, aad2000c02v1SilenceTrapEnable, 
				aad2000c02v1Overload, aad2000c02v1OverloadTrapEnable, aad2000c02v1VuLevel, aad2000c02v1PkLevel, aad2000c02v1SerialNo }
			STATUS current
			DESCRIPTION
				"Module AAD2000C02V1 Group"
			::= { varGroups 460201 }

		-- 1.3.6.1.4.1.10106.2.3.1.460301
		aad2000c03v1ModuleGroup OBJECT-GROUP
			OBJECTS {aad2000c03v1Index, aad2000c03v1Input, aad2000c03v1BckTxEn, aad2000c03v1LedMode, aad2000c03v1Vu8dbu, 
				aad2000c03v1OvlThrLevel, aad2000c03v1SilThrLevel, aad2000c03v1NoSigTout, aad2000c03v1Silence, aad2000c03v1SilenceTrapEnable, 
				aad2000c03v1Overload, aad2000c03v1OverloadTrapEnable, aad2000c03v1VuLevel, aad2000c03v1PkLevel, aad2000c03v1SerialNo }
			STATUS current
			DESCRIPTION
				"Module AAD2000C03V1 Group"
			::= { varGroups 460301 }

		-- 1.3.6.1.4.1.10106.2.3.1.460401
		aad2000c04v1ModuleGroup OBJECT-GROUP
			OBJECTS {aad2000c04v1Index, aad2000c04v1Input, aad2000c04v1BckTxEn, aad2000c04v1LedMode, aad2000c04v1Vu8dbu, 
				aad2000c04v1OvlThrLevel, aad2000c04v1SilThrLevel, aad2000c04v1NoSigTout, aad2000c04v1Silence, aad2000c04v1SilenceTrapEnable, 
				aad2000c04v1Overload, aad2000c04v1OverloadTrapEnable, aad2000c04v1VuLevel, aad2000c04v1PkLevel, aad2000c04v1SerialNo }
			STATUS current
			DESCRIPTION
				"Module AAD2000C04V1 Group"
			::= { varGroups 460401 }

		-- 1.3.6.1.4.1.10106.2.3.1.461001
		ipa2000c01v1ModuleGroup OBJECT-GROUP
			OBJECTS {ipa2000c01v1Index, ipa2000c01v1ActivePreset, ipa2000c01v1LoadPreset, ipa2000c01v1SavePreset, ipa2000c01v1InputStChRst, 
				ipa2000c01v1InputChRst, ipa2000c01v1StatReset, ipa2000c01v1StatMode, ipa2000c01v1IgmpVersion, ipa2000c01v1Input, 
				ipa2000c01v1InputTrapEnable, ipa2000c01v1SwMode, ipa2000c01v1SwModeTrapEnable, ipa2000c01v1Ch1Prior, ipa2000c01v1Ch1PriorTrapEnable, 
				ipa2000c01v1Ch2Prior, ipa2000c01v1Ch2PriorTrapEnable, ipa2000c01v1MaxTimeOut, ipa2000c01v1EnSeamNondvbt, ipa2000c01v1NarrowPllBw, 
				ipa2000c01v1DvbTMode, ipa2000c01v1DvbTModeTrapEnable, ipa2000c01v1NullPckRtp, ipa2000c01v1TxAsi1En, ipa2000c01v1TxAsi2En, 
				ipa2000c01v1TxAsi1AuxEn, ipa2000c01v1TxAsi2AuxEn, ipa2000c01v1RxIp1Inter, ipa2000c01v1RxIp2Inter, ipa2000c01v1TxIp1Inter, 
				ipa2000c01v1TxIp2Inter, ipa2000c01v1TxIp1OutSel, ipa2000c01v1TxIp2OutSel, ipa2000c01v1EthMode1, ipa2000c01v1EthMode2, 
				ipa2000c01v1Ch1Selection, ipa2000c01v1Ch1SelectionTrapEnable, ipa2000c01v1Ch2Selection, ipa2000c01v1Ch2SelectionTrapEnable, ipa2000c01v1TsSyncLossEn, 
				ipa2000c01v1SyncByErrorEn, ipa2000c01v1PatErrorEn, ipa2000c01v1CcErrorEn, ipa2000c01v1PmtErrorEn, ipa2000c01v1PidErrorEn, 
				ipa2000c01v1PidErrorTime, ipa2000c01v1OutDelay, ipa2000c01v1OutDelayTrapEnable, ipa2000c01v1PacketDelay, ipa2000c01v1PacketDelayTrapEnable, 
				ipa2000c01v1Str1Ena, ipa2000c01v1Str1MulticEna, ipa2000c01v1Str1FecEna, ipa2000c01v1Str1UipDAdd3, ipa2000c01v1Str1UipDAdd2, 
				ipa2000c01v1Str1UipDAdd1, ipa2000c01v1Str1UipDAdd0, ipa2000c01v1Str1MipDAdd3, ipa2000c01v1Str1MipDAdd2, ipa2000c01v1Str1MipDAdd1, 
				ipa2000c01v1Str1MipDAdd0, ipa2000c01v1Str1IgmFAdd3, ipa2000c01v1Str1IgmFAdd2, ipa2000c01v1Str1IgmFAdd1, ipa2000c01v1Str1IgmFAdd0, 
				ipa2000c01v1Str1DPort, ipa2000c01v1RxIp1SrMsk, ipa2000c01v1RxIp1SrMsk2, ipa2000c01v1RxIp1SrMsk1, ipa2000c01v1RxIp1SrMsk0, 
				ipa2000c01v1Str2Ena, ipa2000c01v1Str2MulticEna, ipa2000c01v1Str2FecEna, ipa2000c01v1Str2UipDAdd3, ipa2000c01v1Str2UipDAdd2, 
				ipa2000c01v1Str2UipDAdd1, ipa2000c01v1Str2UipDAdd0, ipa2000c01v1Str2MipDAdd3, ipa2000c01v1Str2MipDAdd2, ipa2000c01v1Str2MipDAdd1, 
				ipa2000c01v1Str2MipDAdd0, ipa2000c01v1Str2IgmFAdd3, ipa2000c01v1Str2IgmFAdd2, ipa2000c01v1Str2IgmFAdd1, ipa2000c01v1Str2IgmFAdd0, 
				ipa2000c01v1Str2DPort, ipa2000c01v1RxIp2SrMsk, ipa2000c01v1RxIp2SrMsk1, ipa2000c01v1RxIp2SrMsk2, ipa2000c01v1RxIp2SrMsk3, 
				ipa2000c01v1Tx1UniEna, ipa2000c01v1Tx1MultiEna, ipa2000c01v1Tx1MipAdd3, ipa2000c01v1Tx1MipAdd2, ipa2000c01v1Tx1MipAdd1, 
				ipa2000c01v1Tx1MipAdd0, ipa2000c01v1Tx1UipAdd3, ipa2000c01v1Tx1UipAdd2, ipa2000c01v1Tx1UipAdd1, ipa2000c01v1Tx1UipAdd0, 
				ipa2000c01v1Tx1SPort, ipa2000c01v1Tx1DPort, ipa2000c01v1Tx1LParam, ipa2000c01v1Tx1FecMode, ipa2000c01v1Tx1DParam, 
				ipa2000c01v1Tx1TspkInIppk, ipa2000c01v1Tx1RowDelay, ipa2000c01v1Tx1ColDelay, ipa2000c01v1TxIp1SrAdd3, ipa2000c01v1TxIp1SrAdd2, 
				ipa2000c01v1TxIp1SrAdd1, ipa2000c01v1TxIp1SrAdd0, ipa2000c01v1TxIp1SrMsk0, ipa2000c01v1TxIp1SrMsk1, ipa2000c01v1TxIp1SrMsk2, 
				ipa2000c01v1TxIp1SrMsk3, ipa2000c01v1Tx2UniEna, ipa2000c01v1Tx2MultiEna, ipa2000c01v1Tx2MipAdd3, ipa2000c01v1Tx2MipAdd2, 
				ipa2000c01v1Tx2MipAdd1, ipa2000c01v1Tx2MipAdd0, ipa2000c01v1Tx2UipAdd3, ipa2000c01v1Tx2UipAdd2, ipa2000c01v1Tx2UipAdd1, 
				ipa2000c01v1Tx2UipAdd0, ipa2000c01v1Tx2SPort, ipa2000c01v1Tx2DPort, ipa2000c01v1Tx2LParam, ipa2000c01v1Tx2FecMode, 
				ipa2000c01v1Tx2DParam, ipa2000c01v1Tx2TspkInIppk, ipa2000c01v1Tx2RowDelay, ipa2000c01v1Tx2ColDelay, ipa2000c01v1TxIp2SrAdd3, 
				ipa2000c01v1TxIp2SrAdd2, ipa2000c01v1TxIp2SrAdd1, ipa2000c01v1TxIp2SrAdd0, ipa2000c01v1TxIp2SrMsk0, ipa2000c01v1TxIp2SrMsk1, 
				ipa2000c01v1TxIp2SrMsk2, ipa2000c01v1TxIp2SrMsk3, ipa2000c01v1Rx1IpRxAdd3, ipa2000c01v1Rx1IpRxAdd2, ipa2000c01v1Rx1IpRxAdd1, 
				ipa2000c01v1Rx1IpRxAdd0, ipa2000c01v1Rx1IpRxPort, ipa2000c01v1Rx1LParam, ipa2000c01v1Rx1FecMode, ipa2000c01v1Rx1PacketSize, 
				ipa2000c01v1Rx1DParam, ipa2000c01v1Rx1TsPcks, ipa2000c01v1Rx1PacketRate, ipa2000c01v1Rx1FecRate, ipa2000c01v1Rx1TimeRst, 
				ipa2000c01v1Rx1LostIpPck, ipa2000c01v1Rx1RecIpPck, ipa2000c01v1Rx1OutOrdPck, ipa2000c01v1Rx1BufferStat, ipa2000c01v1Rx2IpRxAdd3, 
				ipa2000c01v1Rx2IpRxAdd2, ipa2000c01v1Rx2IpRxAdd1, ipa2000c01v1Rx2IpRxAdd0, ipa2000c01v1Rx2IpRxPort, ipa2000c01v1Rx2LParam, 
				ipa2000c01v1Rx2FecMode, ipa2000c01v1Rx2PacketSize, ipa2000c01v1Rx2DParam, ipa2000c01v1Rx2TsPcks, ipa2000c01v1Rx2PacketRate, 
				ipa2000c01v1Rx2FecRate, ipa2000c01v1Rx2TimeRst, ipa2000c01v1Rx2LostIpPck, ipa2000c01v1Rx2RecIpPck, ipa2000c01v1Rx2OutOrdPck, 
				ipa2000c01v1Rx2BufferStat, ipa2000c01v1LocalIpAdd3, ipa2000c01v1LocalIpAdd2, ipa2000c01v1LocalIpAdd1, ipa2000c01v1LocalIpAdd0, 
				ipa2000c01v1LocalIpMask3, ipa2000c01v1LocalIpMask2, ipa2000c01v1LocalIpMask1, ipa2000c01v1LocalIpMask0, ipa2000c01v1LocalIp2Add3, 
				ipa2000c01v1LocalIp2Add2, ipa2000c01v1LocalIp2Add1, ipa2000c01v1LocalIp2Add0, ipa2000c01v1LocalIp2Msk3, ipa2000c01v1LocalIp2Msk2, 
				ipa2000c01v1LocalIp2Msk1, ipa2000c01v1LocalIp2Msk0, ipa2000c01v1LocalIpGway3, ipa2000c01v1LocalIpGway2, ipa2000c01v1LocalIpGway1, 
				ipa2000c01v1LocalIpGway0, ipa2000c01v1SysError, ipa2000c01v1Link1, ipa2000c01v1Link1TrapEnable, ipa2000c01v1System1, 
				ipa2000c01v1System1TrapEnable, ipa2000c01v1Link2, ipa2000c01v1Link2TrapEnable, ipa2000c01v1System2, ipa2000c01v1System2TrapEnable, 
				ipa2000c01v11ppsFail, ipa2000c01v11ppsFailTrapEnable, ipa2000c01v113mhzFail, ipa2000c01v113mhzFailTrapEnable, ipa2000c01v1OutputFail, 
				ipa2000c01v1OutputFailTrapEnable, ipa2000c01v1InputStChange, ipa2000c01v1InputChange, ipa2000c01v1SyncLossErr1, ipa2000c01v1SyncLossErr1TrapEnable, 
				ipa2000c01v1SyncByteErr1, ipa2000c01v1SyncByteErr1TrapEnable, ipa2000c01v1PatError1, ipa2000c01v1PatError1TrapEnable, ipa2000c01v1CcError1, 
				ipa2000c01v1CcError1TrapEnable, ipa2000c01v1PmtError1, ipa2000c01v1PmtError1TrapEnable, ipa2000c01v1PidError1, ipa2000c01v1PidError1TrapEnable, 
				ipa2000c01v1MipError1, ipa2000c01v1MipError1TrapEnable, ipa2000c01v1GlobalError1, ipa2000c01v1GlobalError1TrapEnable, ipa2000c01v1SyncLossErr2, 
				ipa2000c01v1SyncLossErr2TrapEnable, ipa2000c01v1SyncByteErr2, ipa2000c01v1SyncByteErr2TrapEnable, ipa2000c01v1PatError2, ipa2000c01v1PatError2TrapEnable, 
				ipa2000c01v1CcError2, ipa2000c01v1CcError2TrapEnable, ipa2000c01v1PmtError2, ipa2000c01v1PmtError2TrapEnable, ipa2000c01v1PidError2, 
				ipa2000c01v1PidError2TrapEnable, ipa2000c01v1MipError2, ipa2000c01v1MipError2TrapEnable, ipa2000c01v1GlobalError2, ipa2000c01v1GlobalError2TrapEnable, 
				ipa2000c01v1Ch1DelWar, ipa2000c01v1Ch1DelWarTrapEnable, ipa2000c01v1Ch2DelWar, ipa2000c01v1Ch2DelWarTrapEnable, ipa2000c01v1GlobalSeam, 
				ipa2000c01v1GlobalSeamTrapEnable, ipa2000c01v1Channel1Delay, ipa2000c01v1Channel2Delay, ipa2000c01v1ArpValid1, ipa2000c01v1IcmpError1, 
				ipa2000c01v1ArpValid2, ipa2000c01v1IcmpError2, ipa2000c01v1SerialNo, ipa2000c01v1SpeedForce1, ipa2000c01v1SpeedForce2, 
				ipa2000c01v1BadCrcPck1, ipa2000c01v1BadCrcPck2, ipa2000c01v1InpFailMode, ipa2000c01v1PatErrorTime, ipa2000c01v1PmtErrorTime, 
				ipa2000c01v1IpRedTx13, ipa2000c01v1IpRedTx12, ipa2000c01v1IpRedTx11, ipa2000c01v1IpRedTx10, ipa2000c01v1IpRedTx23, 
				ipa2000c01v1IpRedTx22, ipa2000c01v1IpRedTx21, ipa2000c01v1IpRedTx20, ipa2000c01v1TxIpSrcAvai1, ipa2000c01v1TxIpSrcAvai2, 
				ipa2000c01v1Channel1Pck, ipa2000c01v1Channel2Pck, ipa2000c01v1RouterIp13, ipa2000c01v1RouterIp12, ipa2000c01v1RouterIp11, 
				ipa2000c01v1RouterIp10, ipa2000c01v1RouterIp23, ipa2000c01v1RouterIp22, ipa2000c01v1RouterIp21, ipa2000c01v1RouterIp20 }
			STATUS current
			DESCRIPTION
				"Module IPA2000C01V1 Group"
			::= { varGroups 461001 }

		-- 1.3.6.1.4.1.10106.2.3.1.467901
		tle2001c02v1ModuleGroup OBJECT-GROUP
			OBJECTS {tle2001c02v1Index, tle2001c02v1Gpo1, tle2001c02v1Gpo2, tle2001c02v1Gpo3, tle2001c02v1Gpo4, 
				tle2001c02v1InvertGpi1Pol, tle2001c02v1InvertGpi2Pol, tle2001c02v1InvertGpi3Pol, tle2001c02v1InvertGpi4Pol, tle2001c02v1InvertGpo1Pol, 
				tle2001c02v1InvertGpo2Pol, tle2001c02v1InvertGpo3Pol, tle2001c02v1InvertGpo4Pol, tle2001c02v1Gpi1, tle2001c02v1Gpi1TrapEnable, 
				tle2001c02v1Gpi2, tle2001c02v1Gpi2TrapEnable, tle2001c02v1Gpi3, tle2001c02v1Gpi3TrapEnable, tle2001c02v1Gpi4, 
				tle2001c02v1Gpi4TrapEnable, tle2001c02v1RedBoard, tle2001c02v1RedBoardTrapEnable, tle2001c02v1EthLink, tle2001c02v1EthLinkTrapEnable, 
				tle2001c02v1EthRedAct, tle2001c02v1EthRedActTrapEnable, tle2001c02v1SerialNo }
			STATUS current
			DESCRIPTION
				"Module TLE2001C02V1 Group"
			::= { varGroups 467901 }

		-- 1.3.6.1.4.1.10106.2.3.1.469001
		ddf2008c01v1ModuleGroup OBJECT-GROUP
			OBJECTS {ddf2008c01v1Index, ddf2008c01v1ActivePreset, ddf2008c01v1LoadPreset, ddf2008c01v1SavePreset, ddf2008c01v1AesIoMode, 
				ddf2008c01v1AudioFailMode, ddf2008c01v1R2lOut1Src, ddf2008c01v1R2lOut2Src, ddf2008c01v1R2lOut3Src, ddf2008c01v1R2lOut4Src, 
				ddf2008c01v1R2lOut5Src, ddf2008c01v1R2lOut6Src, ddf2008c01v1R2lOut7Src, ddf2008c01v1R2lOut8Src, ddf2008c01v1R2lOut9Src, 
				ddf2008c01v1R2lOut10Src, ddf2008c01v1R2lOut11Src, ddf2008c01v1R2lOut12Src, ddf2008c01v1R2lOut13Src, ddf2008c01v1R2lOut14Src, 
				ddf2008c01v1R2lOut15Src, ddf2008c01v1R2lOut16Src, ddf2008c01v1L2rOut1Src, ddf2008c01v1L2rOut2Src, ddf2008c01v1L2rOut3Src, 
				ddf2008c01v1L2rOut4Src, ddf2008c01v1L2rOut5Src, ddf2008c01v1L2rOut6Src, ddf2008c01v1L2rOut7Src, ddf2008c01v1L2rOut8Src, 
				ddf2008c01v1L2rOut9Src, ddf2008c01v1L2rOut10Src, ddf2008c01v1L2rOut11Src, ddf2008c01v1L2rOut12Src, ddf2008c01v1L2rOut13Src, 
				ddf2008c01v1L2rOut14Src, ddf2008c01v1L2rOut15Src, ddf2008c01v1L2rOut16Src, ddf2008c01v1Aes1LOutSrc, ddf2008c01v1Aes1ROutSrc, 
				ddf2008c01v1Aes2LOutSrc, ddf2008c01v1Aes2ROutSrc, ddf2008c01v1Aes3LOutSrc, ddf2008c01v1Aes3ROutSrc, ddf2008c01v1Aes4LOutSrc, 
				ddf2008c01v1Aes4ROutSrc, ddf2008c01v1Aes5LOutSrc, ddf2008c01v1Aes5ROutSrc, ddf2008c01v1Aes6LOutSrc, ddf2008c01v1Aes6ROutSrc, 
				ddf2008c01v1Aes7LOutSrc, ddf2008c01v1Aes7ROutSrc, ddf2008c01v1Aes8LOutSrc, ddf2008c01v1Aes8ROutSrc, ddf2008c01v1AesIn1Pres, 
				ddf2008c01v1AesIn2Pres, ddf2008c01v1AesIn3Pres, ddf2008c01v1AesIn4Pres, ddf2008c01v1AesIn5Pres, ddf2008c01v1AesIn6Pres, 
				ddf2008c01v1AesIn7Pres, ddf2008c01v1AesIn8Pres, ddf2008c01v1AesIn1Locked, ddf2008c01v1AesIn2Locked, ddf2008c01v1AesIn3Locked, 
				ddf2008c01v1AesIn4Locked, ddf2008c01v1AesIn5Locked, ddf2008c01v1AesIn6Locked, ddf2008c01v1AesIn7Locked, ddf2008c01v1AesIn8Locked, 
				ddf2008c01v1BackplaneLocked, ddf2008c01v1BackplaneLockedTrapEnable, ddf2008c01v1L2rIn1Pres, ddf2008c01v1L2rIn2Pres, ddf2008c01v1L2rIn3Pres, 
				ddf2008c01v1L2rIn4Pres, ddf2008c01v1L2rIn5Pres, ddf2008c01v1L2rIn6Pres, ddf2008c01v1L2rIn7Pres, ddf2008c01v1L2rIn8Pres, 
				ddf2008c01v1L2rIn9Pres, ddf2008c01v1L2rIn10Pres, ddf2008c01v1L2rIn11Pres, ddf2008c01v1L2rIn12Pres, ddf2008c01v1L2rIn13Pres, 
				ddf2008c01v1L2rIn14Pres, ddf2008c01v1L2rIn15Pres, ddf2008c01v1L2rIn16Pres, ddf2008c01v1R2lIn1Pres, ddf2008c01v1R2lIn2Pres, 
				ddf2008c01v1R2lIn3Pres, ddf2008c01v1R2lIn4Pres, ddf2008c01v1R2lIn5Pres, ddf2008c01v1R2lIn6Pres, ddf2008c01v1R2lIn7Pres, 
				ddf2008c01v1R2lIn8Pres, ddf2008c01v1R2lIn9Pres, ddf2008c01v1R2lIn10Pres, ddf2008c01v1R2lIn11Pres, ddf2008c01v1R2lIn12Pres, 
				ddf2008c01v1R2lIn13Pres, ddf2008c01v1R2lIn14Pres, ddf2008c01v1R2lIn15Pres, ddf2008c01v1R2lIn16Pres, ddf2008c01v1SerialNo }
			STATUS current
			DESCRIPTION
				"Module DDF2008C01V1 Group"
			::= { varGroups 469001 }

		-- 1.3.6.1.4.1.10106.2.3.1.470001
		hfs2000c01v1ModuleGroup OBJECT-GROUP
			OBJECTS {hfs2000c01v1Index, hfs2000c01v1SynchroMode, hfs2000c01v1FailMode, hfs2000c01v1VbiMode, hfs2000c01v1DelayMode, 
				hfs2000c01v1HDelay, hfs2000c01v1FrameDelay, hfs2000c01v1VDelay, hfs2000c01v1LumaGain, hfs2000c01v1ChromaGain, 
				hfs2000c01v1BlackOffset, hfs2000c01v1Bits, hfs2000c01v1Grp1P0lSrc, hfs2000c01v1Grp1P0rSrc, hfs2000c01v1Grp1P1lSrc, 
				hfs2000c01v1Grp1P1rSrc, hfs2000c01v1Grp1P0l, hfs2000c01v1Grp1P0r, hfs2000c01v1Grp1P1l, hfs2000c01v1Grp1P1r, 
				hfs2000c01v1Grp2P0lSrc, hfs2000c01v1Grp2P0rSrc, hfs2000c01v1Grp2P1lSrc, hfs2000c01v1Grp2P1rSrc, hfs2000c01v1Grp2P0l, 
				hfs2000c01v1Grp2P0r, hfs2000c01v1Grp2P1l, hfs2000c01v1Grp2P1r, hfs2000c01v1Grp3P0lSrc, hfs2000c01v1Grp3P0rSrc, 
				hfs2000c01v1Grp3P1lSrc, hfs2000c01v1Grp3P1rSrc, hfs2000c01v1Grp3P0l, hfs2000c01v1Grp3P0r, hfs2000c01v1Grp3P1l, 
				hfs2000c01v1Grp3P1r, hfs2000c01v1Grp4P0lSrc, hfs2000c01v1Grp4P0rSrc, hfs2000c01v1Grp4P1lSrc, hfs2000c01v1Grp4P1rSrc, 
				hfs2000c01v1Grp4P0l, hfs2000c01v1Grp4P0r, hfs2000c01v1Grp4P1l, hfs2000c01v1Grp4P1r, hfs2000c01v1NoSig, 
				hfs2000c01v1NoSigTrapEnable, hfs2000c01v1Unlock, hfs2000c01v1UnlockTrapEnable, hfs2000c01v1EdhCrc, hfs2000c01v1EdhCrcTrapEnable, 
				hfs2000c01v1NoRef, hfs2000c01v1NoRefTrapEnable, hfs2000c01v1RefUnlock, hfs2000c01v1RefUnlockTrapEnable, hfs2000c01v1InputFormat, 
				hfs2000c01v1SdiFormat, hfs2000c01v1SigDelay, hfs2000c01v1Grp1Pres, hfs2000c01v1Grp2Pres, hfs2000c01v1Grp3Pres, 
				hfs2000c01v1Grp4Pres, hfs2000c01v1Grp1P0Err, hfs2000c01v1Grp1P1Err, hfs2000c01v1Grp2P0Err, hfs2000c01v1Grp2P1Err, 
				hfs2000c01v1Grp3P0Err, hfs2000c01v1Grp3P1Err, hfs2000c01v1Grp4P0Err, hfs2000c01v1Grp4P1Err, hfs2000c01v1R2lIn1Pres, 
				hfs2000c01v1R2lIn2Pres, hfs2000c01v1R2lIn3Pres, hfs2000c01v1R2lIn4Pres, hfs2000c01v1R2lIn5Pres, hfs2000c01v1R2lIn6Pres, 
				hfs2000c01v1R2lIn7Pres, hfs2000c01v1R2lIn8Pres, hfs2000c01v1R2lIn9Pres, hfs2000c01v1R2lIn10Pres, hfs2000c01v1R2lIn11Pres, 
				hfs2000c01v1R2lIn12Pres, hfs2000c01v1R2lIn13Pres, hfs2000c01v1R2lIn14Pres, hfs2000c01v1R2lIn15Pres, hfs2000c01v1R2lIn16Pres, 
				hfs2000c01v1SerialNo }
			STATUS current
			DESCRIPTION
				"Module HFS2000C01V1 Group"
			::= { varGroups 470001 }

		-- 1.3.6.1.4.1.10106.2.3.1.471001
		htc3000c01v1ModuleGroup OBJECT-GROUP
			OBJECTS {htc3000c01v1Index, htc3000c01v1ActivePreset, htc3000c01v1LoadPreset, htc3000c01v1SavePreset, htc3000c01v1AnaRefFmt, 
				htc3000c01v1DelayMode, htc3000c01v1SynchroMode, htc3000c01v1FailMode, htc3000c01v1InitFmt, htc3000c01v1GenEn, 
				htc3000c01v1HDelay, htc3000c01v1VDelay, htc3000c01v1ModeTc, htc3000c01v1SrcTc, htc3000c01v1DropFr, 
				htc3000c01v1Bgf, htc3000c01v1EnDlsave, htc3000c01v1DateFormat, htc3000c01v1DvitcIns, htc3000c01v1AtcIns, 
				htc3000c01v1AtcType, htc3000c01v1OsdIns, htc3000c01v1OsdPosition, htc3000c01v1AuxGen, htc3000c01v1ClockFormat, 
				htc3000c01v1ClockAmPm, htc3000c01v1ClockSize, htc3000c01v1LevelPips, htc3000c01v1MediasGen, htc3000c01v1FreqPips, 
				htc3000c01v1NPipsHour, htc3000c01v1NPipsHalf, htc3000c01v1ShortPerHour, htc3000c01v1ShortPerHalf, htc3000c01v1LongPerHour, 
				htc3000c01v1LongPerHalf, htc3000c01v1SumMonthSt, htc3000c01v1SumWeekSt, htc3000c01v1SumWDaySt, htc3000c01v1SumHourSt, 
				htc3000c01v1SumHourOffset, htc3000c01v1WinMonthSt, htc3000c01v1WinWeekSt, htc3000c01v1WinWDaySt, htc3000c01v1WinHourSt, 
				htc3000c01v1WinHourOffset, htc3000c01v1RefAbsent, htc3000c01v1RefAbsentTrapEnable, htc3000c01v1RefUnlock, htc3000c01v1RefUnlockTrapEnable, 
				htc3000c01v1NoSignalMain, htc3000c01v1NoSignalMainTrapEnable, htc3000c01v1UnlockMain, htc3000c01v1UnlockMainTrapEnable, htc3000c01v1EdhErrorMain, 
				htc3000c01v1EdhErrorMainTrapEnable, htc3000c01v1NoSignalAux, htc3000c01v1NoSignalAuxTrapEnable, htc3000c01v1UnlockAux, htc3000c01v1UnlockAuxTrapEnable, 
				htc3000c01v1EdhErrorAux, htc3000c01v1EdhErrorAuxTrapEnable, htc3000c01v1IncompFmt, htc3000c01v1IncompFmtTrapEnable, htc3000c01v1TcFail, 
				htc3000c01v1TcFailTrapEnable, htc3000c01v1FormatRef, htc3000c01v1FormatMainIn, htc3000c01v1FormatAuxIn, htc3000c01v1FormatMainTx, 
				htc3000c01v1SigDelay, htc3000c01v1DvitcPres, htc3000c01v1AtcVitcPres, htc3000c01v1AtcLtcPres, htc3000c01v1LtcPres, 
				htc3000c01v1BgfSt, htc3000c01v1DropFSt, htc3000c01v1ColorFSt, htc3000c01v1SerialNo, htc3000c01v1DateFmtRx, 
				htc3000c01v1EnDateGen }
			STATUS current
			DESCRIPTION
				"Module HTC3000C01V1 Group"
			::= { varGroups 471001 }

		-- 1.3.6.1.4.1.10106.2.3.1.473501
		tle3001c02v1ModuleGroup OBJECT-GROUP
			OBJECTS {tle3001c02v1Index, tle3001c02v1Serial485232, tle3001c02v1ConsoleEna, tle3001c02v1Gpo1, tle3001c02v1Gpo2, 
				tle3001c02v1Gpo3, tle3001c02v1Gpo4, tle3001c02v1InvertGpi1Pol, tle3001c02v1InvertGpi2Pol, tle3001c02v1InvertGpi3Pol, 
				tle3001c02v1InvertGpi4Pol, tle3001c02v1InvertGpo1Pol, tle3001c02v1InvertGpo2Pol, tle3001c02v1InvertGpo3Pol, tle3001c02v1InvertGpo4Pol, 
				tle3001c02v1Gpi1, tle3001c02v1Gpi1TrapEnable, tle3001c02v1Gpi2, tle3001c02v1Gpi2TrapEnable, tle3001c02v1Gpi3, 
				tle3001c02v1Gpi3TrapEnable, tle3001c02v1Gpi4, tle3001c02v1Gpi4TrapEnable, tle3001c02v1RedBoard, tle3001c02v1RedBoardTrapEnable, 
				tle3001c02v1EthLink, tle3001c02v1EthLinkTrapEnable, tle3001c02v1EthRedAct, tle3001c02v1EthRedActTrapEnable, tle3001c02v1SerialNo }
			STATUS current
			DESCRIPTION
				"Module TLE3001C02V1 Group"
			::= { varGroups 473501 }

		-- 1.3.6.1.4.1.10106.2.3.1.474701
		adf2008c01v1ModuleGroup OBJECT-GROUP
			OBJECTS {adf2008c01v1Index, adf2008c01v1ActivePreset, adf2008c01v1LoadPreset, adf2008c01v1SavePreset, adf2008c01v1R2lOut1Src, 
				adf2008c01v1R2lOut2Src, adf2008c01v1R2lOut3Src, adf2008c01v1R2lOut4Src, adf2008c01v1R2lOut5Src, adf2008c01v1R2lOut6Src, 
				adf2008c01v1R2lOut7Src, adf2008c01v1R2lOut8Src, adf2008c01v1R2lOut9Src, adf2008c01v1R2lOut10Src, adf2008c01v1R2lOut11Src, 
				adf2008c01v1R2lOut12Src, adf2008c01v1R2lOut13Src, adf2008c01v1R2lOut14Src, adf2008c01v1R2lOut15Src, adf2008c01v1R2lOut16Src, 
				adf2008c01v1L2rOut1Src, adf2008c01v1L2rOut2Src, adf2008c01v1L2rOut3Src, adf2008c01v1L2rOut4Src, adf2008c01v1L2rOut5Src, 
				adf2008c01v1L2rOut6Src, adf2008c01v1L2rOut7Src, adf2008c01v1L2rOut8Src, adf2008c01v1L2rOut9Src, adf2008c01v1L2rOut10Src, 
				adf2008c01v1L2rOut11Src, adf2008c01v1L2rOut12Src, adf2008c01v1L2rOut13Src, adf2008c01v1L2rOut14Src, adf2008c01v1L2rOut15Src, 
				adf2008c01v1L2rOut16Src, adf2008c01v1GainIn1, adf2008c01v1GainIn2, adf2008c01v1GainIn3, adf2008c01v1GainIn4, 
				adf2008c01v1GainIn5, adf2008c01v1GainIn6, adf2008c01v1GainIn7, adf2008c01v1GainIn8, adf2008c01v1AnalogIn1Level, 
				adf2008c01v1AnalogIn2Level, adf2008c01v1AnalogIn3Level, adf2008c01v1AnalogIn4Level, adf2008c01v1AnalogIn5Level, adf2008c01v1AnalogIn6Level, 
				adf2008c01v1AnalogIn7Level, adf2008c01v1AnalogIn8Level, adf2008c01v1BackplaneLocked, adf2008c01v1BackplaneLockedTrapEnable, adf2008c01v1L2rIn1Pres, 
				adf2008c01v1L2rIn2Pres, adf2008c01v1L2rIn3Pres, adf2008c01v1L2rIn4Pres, adf2008c01v1L2rIn5Pres, adf2008c01v1L2rIn6Pres, 
				adf2008c01v1L2rIn7Pres, adf2008c01v1L2rIn8Pres, adf2008c01v1L2rIn9Pres, adf2008c01v1L2rIn10Pres, adf2008c01v1L2rIn11Pres, 
				adf2008c01v1L2rIn12Pres, adf2008c01v1L2rIn13Pres, adf2008c01v1L2rIn14Pres, adf2008c01v1L2rIn15Pres, adf2008c01v1L2rIn16Pres, 
				adf2008c01v1R2lIn1Pres, adf2008c01v1R2lIn2Pres, adf2008c01v1R2lIn3Pres, adf2008c01v1R2lIn4Pres, adf2008c01v1R2lIn5Pres, 
				adf2008c01v1R2lIn6Pres, adf2008c01v1R2lIn7Pres, adf2008c01v1R2lIn8Pres, adf2008c01v1R2lIn9Pres, adf2008c01v1R2lIn10Pres, 
				adf2008c01v1R2lIn11Pres, adf2008c01v1R2lIn12Pres, adf2008c01v1R2lIn13Pres, adf2008c01v1R2lIn14Pres, adf2008c01v1R2lIn15Pres, 
				adf2008c01v1R2lIn16Pres, adf2008c01v1AnalogInOverfl, adf2008c01v1AnalogInOverflTrapEnable, adf2008c01v1SerialNo, adf2008c01v1OverloadAlarm1, 
				adf2008c01v1OverloadAlarm2, adf2008c01v1OverloadAlarm3, adf2008c01v1OverloadAlarm4, adf2008c01v1OverloadAlarm5, adf2008c01v1OverloadAlarm6, 
				adf2008c01v1OverloadAlarm7, adf2008c01v1OverloadAlarm8 }
			STATUS current
			DESCRIPTION
				"Module ADF2008C01V1 Group"
			::= { varGroups 474701 }

		-- 1.3.6.1.4.1.10106.2.3.1.474801
		daf2008c01v1ModuleGroup OBJECT-GROUP
			OBJECTS {daf2008c01v1Index, daf2008c01v1ActivePreset, daf2008c01v1LoadPreset, daf2008c01v1SavePreset, daf2008c01v1AudioFailMode, 
				daf2008c01v1Aes1LOutSrc, daf2008c01v1Aes1ROutSrc, daf2008c01v1Aes2LOutSrc, daf2008c01v1Aes2ROutSrc, daf2008c01v1Aes3LOutSrc, 
				daf2008c01v1Aes3ROutSrc, daf2008c01v1Aes4LOutSrc, daf2008c01v1Aes4ROutSrc, daf2008c01v1GainOut1, daf2008c01v1GainOut2, 
				daf2008c01v1GainOut3, daf2008c01v1GainOut4, daf2008c01v1GainOut5, daf2008c01v1GainOut6, daf2008c01v1GainOut7, 
				daf2008c01v1GainOut8, daf2008c01v1AesOut1Level, daf2008c01v1AesOut2Level, daf2008c01v1AesOut3Level, daf2008c01v1AesOut4Level, 
				daf2008c01v1AesOut5Level, daf2008c01v1AesOut6Level, daf2008c01v1AesOut7Level, daf2008c01v1AesOut8Level, daf2008c01v1BackplaneLocked, 
				daf2008c01v1BackplaneLockedTrapEnable, daf2008c01v1L2rIn1Pres, daf2008c01v1L2rIn2Pres, daf2008c01v1L2rIn3Pres, daf2008c01v1L2rIn4Pres, 
				daf2008c01v1L2rIn5Pres, daf2008c01v1L2rIn6Pres, daf2008c01v1L2rIn7Pres, daf2008c01v1L2rIn8Pres, daf2008c01v1L2rIn9Pres, 
				daf2008c01v1L2rIn10Pres, daf2008c01v1L2rIn11Pres, daf2008c01v1L2rIn12Pres, daf2008c01v1L2rIn13Pres, daf2008c01v1L2rIn14Pres, 
				daf2008c01v1L2rIn15Pres, daf2008c01v1L2rIn16Pres, daf2008c01v1R2lIn1Pres, daf2008c01v1R2lIn2Pres, daf2008c01v1R2lIn3Pres, 
				daf2008c01v1R2lIn4Pres, daf2008c01v1R2lIn5Pres, daf2008c01v1R2lIn6Pres, daf2008c01v1R2lIn7Pres, daf2008c01v1R2lIn8Pres, 
				daf2008c01v1R2lIn9Pres, daf2008c01v1R2lIn10Pres, daf2008c01v1R2lIn11Pres, daf2008c01v1R2lIn12Pres, daf2008c01v1R2lIn13Pres, 
				daf2008c01v1R2lIn14Pres, daf2008c01v1R2lIn15Pres, daf2008c01v1R2lIn16Pres, daf2008c01v1SerialNo, daf2008c01v1OverloadAlarm1, 
				daf2008c01v1OverloadAlarm2, daf2008c01v1OverloadAlarm3, daf2008c01v1OverloadAlarm4, daf2008c01v1OverloadAlarm5, daf2008c01v1OverloadAlarm6, 
				daf2008c01v1OverloadAlarm7, daf2008c01v1OverloadAlarm8 }
			STATUS current
			DESCRIPTION
				"Module DAF2008C01V1 Group"
			::= { varGroups 474801 }

		-- 1.3.6.1.4.1.10106.2.3.1.478401
		tly3032c04v1ModuleGroup OBJECT-GROUP
			OBJECTS {tly3032c04v1Index, tly3032c04v1Gpi1, tly3032c04v1Gpi1TrapEnable, tly3032c04v1Gpi2, tly3032c04v1Gpi2TrapEnable, 
				tly3032c04v1Gpi3, tly3032c04v1Gpi3TrapEnable, tly3032c04v1Gpi4, tly3032c04v1Gpi4TrapEnable, tly3032c04v1Gpi5, 
				tly3032c04v1Gpi5TrapEnable, tly3032c04v1Gpi6, tly3032c04v1Gpi6TrapEnable, tly3032c04v1Gpi7, tly3032c04v1Gpi7TrapEnable, 
				tly3032c04v1Gpi8, tly3032c04v1Gpi8TrapEnable, tly3032c04v1Gpi9, tly3032c04v1Gpi9TrapEnable, tly3032c04v1Gpi10, 
				tly3032c04v1Gpi10TrapEnable, tly3032c04v1Gpi11, tly3032c04v1Gpi11TrapEnable, tly3032c04v1Gpi12, tly3032c04v1Gpi12TrapEnable, 
				tly3032c04v1Gpi13, tly3032c04v1Gpi13TrapEnable, tly3032c04v1Gpi14, tly3032c04v1Gpi14TrapEnable, tly3032c04v1Gpi15, 
				tly3032c04v1Gpi15TrapEnable, tly3032c04v1Gpi16, tly3032c04v1Gpi16TrapEnable, tly3032c04v1Gpi17, tly3032c04v1Gpi17TrapEnable, 
				tly3032c04v1Gpi18, tly3032c04v1Gpi18TrapEnable, tly3032c04v1Gpi19, tly3032c04v1Gpi19TrapEnable, tly3032c04v1Gpi20, 
				tly3032c04v1Gpi20TrapEnable, tly3032c04v1Gpi21, tly3032c04v1Gpi21TrapEnable, tly3032c04v1Gpi22, tly3032c04v1Gpi22TrapEnable, 
				tly3032c04v1Gpi23, tly3032c04v1Gpi23TrapEnable, tly3032c04v1Gpi24, tly3032c04v1Gpi24TrapEnable, tly3032c04v1Gpi25, 
				tly3032c04v1Gpi25TrapEnable, tly3032c04v1Gpi26, tly3032c04v1Gpi26TrapEnable, tly3032c04v1Gpi27, tly3032c04v1Gpi27TrapEnable, 
				tly3032c04v1Gpi28, tly3032c04v1Gpi28TrapEnable, tly3032c04v1Gpi29, tly3032c04v1Gpi29TrapEnable, tly3032c04v1Gpi30, 
				tly3032c04v1Gpi30TrapEnable, tly3032c04v1Gpi31, tly3032c04v1Gpi31TrapEnable, tly3032c04v1Gpi32, tly3032c04v1Gpi32TrapEnable }
			STATUS current
			DESCRIPTION
				"Module TLY3032C04V1 Group"
			::= { varGroups 478401 }

		-- 1.3.6.1.4.1.10106.2.3.1.478901
		tle0001c02v1ModuleGroup OBJECT-GROUP
			OBJECTS {tle0001c02v1Index, tle0001c02v1SerialNo, tle0001c02v1App1Ena, tle0001c02v1App1EnaTrapEnable, tle0001c02v1App2Ena, 
				tle0001c02v1App3Ena }
			STATUS current
			DESCRIPTION
				"Module TLE0001C02V1 Group"
			::= { varGroups 478901 }

		-- 1.3.6.1.4.1.10106.2.3.1.483501
		udp2000c01v1ModuleGroup OBJECT-GROUP
			OBJECTS {udp2000c01v1Index, udp2000c01v1ActivePreset, udp2000c01v1LoadPreset, udp2000c01v1SavePreset, udp2000c01v1EthMode2, 
				udp2000c01v1SpeedForce2, udp2000c01v1TxtInsEn, udp2000c01v1TxtExtEn, udp2000c01v1TimeCodeInsEn, udp2000c01v1VideoCleanEn, 
				udp2000c01v1VidFreeRunEn, udp2000c01v1PingEnable, udp2000c01v1LocalIpAdd3, udp2000c01v1LocalIpAdd2, udp2000c01v1LocalIpAdd1, 
				udp2000c01v1LocalIpAdd0, udp2000c01v1DstPortMsb, udp2000c01v1DstPortLsb, udp2000c01v1TxUipAdd3, udp2000c01v1TxUipAdd2, 
				udp2000c01v1TxUipAdd1, udp2000c01v1TxUipAdd0, udp2000c01v1TxDPortMsb, udp2000c01v1TxDPortLsb, udp2000c01v1LocalIpGway3, 
				udp2000c01v1LocalIpGway2, udp2000c01v1LocalIpGway1, udp2000c01v1LocalIpGway0, udp2000c01v1LocalIpMask3, udp2000c01v1LocalIpMask2, 
				udp2000c01v1LocalIpMask1, udp2000c01v1LocalIpMask0, udp2000c01v1NoSignal, udp2000c01v1NoSignalTrapEnable, udp2000c01v1Unlock, 
				udp2000c01v1UnlockTrapEnable, udp2000c01v1EdhError, udp2000c01v1FormatB, udp2000c01v1DestAvailable, udp2000c01v1DestAvailableTrapEnable, 
				udp2000c01v1PingStatus, udp2000c01v1PingStatusTrapEnable, udp2000c01v1EmbedderFail, udp2000c01v1EmbedderFailTrapEnable, udp2000c01v1DeembedderFail, 
				udp2000c01v1DeembedderFailTrapEnable, udp2000c01v1EmbedderValid, udp2000c01v1EmbedderValidTrapEnable, udp2000c01v1DeembedderValid, udp2000c01v1DeembedderValidTrapEnable, 
				udp2000c01v1Link2, udp2000c01v1System2, udp2000c01v1VitcAtcPres, udp2000c01v1VitcAtcPresTrapEnable, udp2000c01v1SerialNo }
			STATUS current
			DESCRIPTION
				"Module UDP2000C01V1 Group"
			::= { varGroups 483501 }

		-- 1.3.6.1.4.1.10106.2.3.1.484901
		aem2008c01v1ModuleGroup OBJECT-GROUP
			OBJECTS {aem2008c01v1Index, aem2008c01v1Section, aem2008c01v1FrqSamp, aem2008c01v1CleanH, aem2008c01v1CoarseGain, 
				aem2008c01v1SdiInFail, aem2008c01v1SdiInFailTrapEnable, aem2008c01v1EdhInFail, aem2008c01v1EdhInFailTrapEnable, aem2008c01v1AudFail, 
				aem2008c01v1AudFailTrapEnable, aem2008c01v1AudClip, aem2008c01v1AudClipTrapEnable, aem2008c01v1Fmt, aem2008c01v1G1Pres, 
				aem2008c01v1G2Pres, aem2008c01v1G3Pres, aem2008c01v1G4Pres, aem2008c01v1Mpx1Pres, aem2008c01v1Mpx2Pres, 
				aem2008c01v1Mpx3Pres, aem2008c01v1Mpx4Pres, aem2008c01v1SerialNo, aem2008c01v1Invert, aem2008c01v1Ref27mFail }
			STATUS current
			DESCRIPTION
				"Module AEM2008C01V1 Group"
			::= { varGroups 484901 }

		-- 1.3.6.1.4.1.10106.2.3.1.485001
		ade2008c01v1ModuleGroup OBJECT-GROUP
			OBJECTS {ade2008c01v1Index, ade2008c01v1Section, ade2008c01v1FrqSamp, ade2008c01v1CleanH, ade2008c01v1CoarseGain, 
				ade2008c01v1SdiInFail, ade2008c01v1SdiInFailTrapEnable, ade2008c01v1EdhInFail, ade2008c01v1EdhInFailTrapEnable, ade2008c01v1AudFail, 
				ade2008c01v1AudFailTrapEnable, ade2008c01v1AudClip, ade2008c01v1AudClipTrapEnable, ade2008c01v1Fmt, ade2008c01v1G1Pres, 
				ade2008c01v1G2Pres, ade2008c01v1G3Pres, ade2008c01v1G4Pres, ade2008c01v1Mpx1Pres, ade2008c01v1Mpx2Pres, 
				ade2008c01v1Mpx3Pres, ade2008c01v1Mpx4Pres, ade2008c01v1SerialNo, ade2008c01v1Invert }
			STATUS current
			DESCRIPTION
				"Module ADE2008C01V1 Group"
			::= { varGroups 485001 }

		-- 1.3.6.1.4.1.10106.2.3.1.485901
		htg3001c01v1ModuleGroup OBJECT-GROUP
			OBJECTS {htg3001c01v1Index, htg3001c01v1ExpRefFormat, htg3001c01v1ExpRefFormatTrapEnable, htg3001c01v1RefInput, htg3001c01v1RefInputTrapEnable, 
				htg3001c01v1MeasInput, htg3001c01v1OutFormat1, htg3001c01v1OutFormat1TrapEnable, htg3001c01v1OutMute1, htg3001c01v1HDelay1, 
				htg3001c01v1VDelay1, htg3001c01v1TestSignal1, htg3001c01v1EnGrp1Aud1, htg3001c01v1EnGrp2Aud1, htg3001c01v1EnGrp3Aud1, 
				htg3001c01v1EnGrp4Aud1, htg3001c01v1EnOsd1, htg3001c01v1AudFrP0G01, htg3001c01v1AudFrP1G01, htg3001c01v1AudFrP0G11, 
				htg3001c01v1AudFrP1G11, htg3001c01v1AudFrP0G21, htg3001c01v1AudFrP1G21, htg3001c01v1AudFrP0G31, htg3001c01v1AudFrP1G31, 
				htg3001c01v1AudDipP0G01, htg3001c01v1AudDipP1G01, htg3001c01v1AudDipP0G11, htg3001c01v1AudDipP1G11, htg3001c01v1AudDipP0G21, 
				htg3001c01v1AudDipP1G21, htg3001c01v1AudDipP0G31, htg3001c01v1AudDipP1G31, htg3001c01v1AudLevP0G01, htg3001c01v1AudLevP0G11, 
				htg3001c01v1AudLevP1G01, htg3001c01v1AudLevP1G11, htg3001c01v1AudLevP0G21, htg3001c01v1AudLevP1G21, htg3001c01v1AudLevP0G31, 
				htg3001c01v1AudLevP1G31, htg3001c01v1OutFormat2, htg3001c01v1OutFormat2TrapEnable, htg3001c01v1OutMute2, htg3001c01v1HDelay2, 
				htg3001c01v1VDelay2, htg3001c01v1TestSignal2, htg3001c01v1EnGrp1Aud2, htg3001c01v1EnGrp2Aud2, htg3001c01v1EnGrp3Aud2, 
				htg3001c01v1EnGrp4Aud2, htg3001c01v1EnOsd2, htg3001c01v1AudFrP0G02, htg3001c01v1AudFrP1G02, htg3001c01v1AudFrP0G12, 
				htg3001c01v1AudFrP1G12, htg3001c01v1AudFrP0G22, htg3001c01v1AudFrP1G22, htg3001c01v1AudFrP0G32, htg3001c01v1AudFrP1G32, 
				htg3001c01v1AudDipP0G02, htg3001c01v1AudDipP1G02, htg3001c01v1AudDipP0G12, htg3001c01v1AudDipP1G12, htg3001c01v1AudDipP0G22, 
				htg3001c01v1AudDipP1G22, htg3001c01v1AudDipP0G32, htg3001c01v1AudDipP1G32, htg3001c01v1AudLevP0G02, htg3001c01v1AudLevP0G12, 
				htg3001c01v1AudLevP1G02, htg3001c01v1AudLevP1G12, htg3001c01v1AudLevP0G22, htg3001c01v1AudLevP1G22, htg3001c01v1AudLevP0G32, 
				htg3001c01v1AudLevP1G32, htg3001c01v1OutFormat3, htg3001c01v1OutFormat3TrapEnable, htg3001c01v1HDelay3, htg3001c01v1VDelay3, 
				htg3001c01v1Sch3, htg3001c01v1ArefFailMsk, htg3001c01v1DrefFailMsk, htg3001c01v1IrefFailMsk, htg3001c01v1RefIncFailMsk, 
				htg3001c01v1RefLckFailMsk, htg3001c01v1SumMonthSt, htg3001c01v1SumWeekSt, htg3001c01v1SumWDaySt, htg3001c01v1SumHourSt, 
				htg3001c01v1SumHourOffset, htg3001c01v1WinMonthSt, htg3001c01v1WinWeekSt, htg3001c01v1WinWDaySt, htg3001c01v1WinHourSt, 
				htg3001c01v1WinHourOffset, htg3001c01v1EnDlsave, htg3001c01v1DropFrame, htg3001c01v1Bgf, htg3001c01v1DateFormat, 
				htg3001c01v1EnDateGen, htg3001c01v1AdjHourDay, htg3001c01v1ArefFail, htg3001c01v1ArefFailTrapEnable, htg3001c01v1DrefFail, 
				htg3001c01v1DrefFailTrapEnable, htg3001c01v1IrefFail, htg3001c01v1IrefFailTrapEnable, htg3001c01v1RefIncFail, htg3001c01v1RefIncFailTrapEnable, 
				htg3001c01v1RefLockFail, htg3001c01v1RefLockFailTrapEnable, htg3001c01v1DrefCrcFail, htg3001c01v1DrefCrcFailTrapEnable, htg3001c01v1TcFail, 
				htg3001c01v1ArefFormat, htg3001c01v1ArefFormatTrapEnable, htg3001c01v1DrefFormat, htg3001c01v1DrefFormatTrapEnable, htg3001c01v1MeasDelay, 
				htg3001c01v1MeasFreq, htg3001c01v1SerialNo, htg3001c01v1OsdDly1, htg3001c01v1OsdDly2, htg3001c01v1AvDlyBlack, 
				htg3001c01v1AvDlySil, htg3001c01v1DelayG1p0l, htg3001c01v1DelayG1p0r, htg3001c01v1DelayG1p1l, htg3001c01v1DelayG1p1r, 
				htg3001c01v1DelayG2p0l, htg3001c01v1DelayG2p0r, htg3001c01v1DelayG2p1l, htg3001c01v1DelayG2p1r, htg3001c01v1DelayG3p0l, 
				htg3001c01v1DelayG3p0r, htg3001c01v1DelayG3p1l, htg3001c01v1DelayG3p1r, htg3001c01v1DelayG4p0l, htg3001c01v1DelayG4p0r, 
				htg3001c01v1DelayG4p1l, htg3001c01v1DelayG4p1r, htg3001c01v1AvSeqG1p0, htg3001c01v1AvSeqG1p1, htg3001c01v1AvSeqG2p0, 
				htg3001c01v1AvSeqG2p1, htg3001c01v1AvSeqG3p0, htg3001c01v1AvSeqG3p1, htg3001c01v1AvSeqG4p0, htg3001c01v1AvSeqG4p1, 
				htg3001c01v1AudGrpPres1, htg3001c01v1AudGrpPres2, htg3001c01v1AudGrpPres3, htg3001c01v1AudGrpPres4, htg3001c01v1AvSeqPhase }
			STATUS current
			DESCRIPTION
				"Module HTG3001C01V1 Group"
			::= { varGroups 485901 }

		-- 1.3.6.1.4.1.10106.2.3.1.494401
		psu3300c03v1ModuleGroup OBJECT-GROUP
			OBJECTS {psu3300c03v1Index, psu3300c03v1PowerOff, psu3300c03v1PowerOffTrapEnable, psu3300c03v1TempWarning, psu3300c03v1TempWarningTrapEnable, 
				psu3300c03v1TempFail, psu3300c03v1TempFailTrapEnable, psu3300c03v1ActTemp, psu3300c03v1MeanTemp, psu3300c03v1MaxTemp, 
				psu3300c03v1PonHours, psu3300c03v1TotMaxTemp, psu3300c03v1TotPonHours, psu3300c03v1TotPonTimes, psu3300c03v1SerialNo, 
				psu3300c03v1InputVolt }
			STATUS current
			DESCRIPTION
				"Module PSU3300C03V1 Group"
			::= { varGroups 494401 }

		-- 1.3.6.1.4.1.10106.2.3.1.496001
		ttd3000c03v1ModuleGroup OBJECT-GROUP
			OBJECTS {ttd3000c03v1Index, ttd3000c03v1Mode, ttd3000c03v1ModeTrapEnable, ttd3000c03v1InputA, ttd3000c03v1InputATrapEnable, 
				ttd3000c03v1InputB, ttd3000c03v1InputBTrapEnable, ttd3000c03v1Impedance, ttd3000c03v1FreqRange, ttd3000c03v1ExpectedFreq, 
				ttd3000c03v1FreqFailOffset, ttd3000c03v1InputALvFail, ttd3000c03v1InputALvFailTrapEnable, ttd3000c03v1InputAFrFail, ttd3000c03v1InputAFrFailTrapEnable, 
				ttd3000c03v1InputBLbFail, ttd3000c03v1InputBLbFailTrapEnable, ttd3000c03v1InputBFrFail, ttd3000c03v1InputBFrFailTrapEnable, ttd3000c03v1FreqA, 
				ttd3000c03v1FreqB, ttd3000c03v1SerialNo }
			STATUS current
			DESCRIPTION
				"Module TTD3000C03V1 Group"
			::= { varGroups 496001 }

		-- 1.3.6.1.4.1.10106.2.3.1.497501
		adb2008c01v1ModuleGroup OBJECT-GROUP
			OBJECTS {adb2008c01v1Index, adb2008c01v1ActivePreset, adb2008c01v1LoadPreset, adb2008c01v1SavePreset, adb2008c01v1ManNAuto, 
				adb2008c01v1BaseSlot, adb2008c01v1SlotUsed, adb2008c01v1OvldLevel, adb2008c01v1Gain0, adb2008c01v1Phase0, 
				adb2008c01v1Gain1, adb2008c01v1Phase1, adb2008c01v1Gain2, adb2008c01v1Phase2, adb2008c01v1Gain3, 
				adb2008c01v1Phase3, adb2008c01v1Gain4, adb2008c01v1Phase4, adb2008c01v1Gain5, adb2008c01v1Phase5, 
				adb2008c01v1Gain6, adb2008c01v1Phase6, adb2008c01v1Gain7, adb2008c01v1Phase7, adb2008c01v1BusTimFail, 
				adb2008c01v1BusTimFailTrapEnable, adb2008c01v1BusTimUnlck, adb2008c01v1BusTimUnlckTrapEnable, adb2008c01v1BusAudFail, adb2008c01v1BusAudFailTrapEnable, 
				adb2008c01v1BusAudError, adb2008c01v1BusAudErrorTrapEnable, adb2008c01v1AudClipEr, adb2008c01v1AudClipErTrapEnable, adb2008c01v1AudInsFail, 
				adb2008c01v1AudInsFailTrapEnable, adb2008c01v1AudOvldFail, adb2008c01v1AudOvldFailTrapEnable, adb2008c01v1Slot1Pres, adb2008c01v1Slot2Pres, 
				adb2008c01v1Slot3Pres, adb2008c01v1Slot4Pres, adb2008c01v1Slot5Pres, adb2008c01v1Slot6Pres, adb2008c01v1Slot7Pres, 
				adb2008c01v1Slot8Pres, adb2008c01v1SerialNo }
			STATUS current
			DESCRIPTION
				"Module ADB2008C01V1 Group"
			::= { varGroups 497501 }

		-- 1.3.6.1.4.1.10106.2.3.1.497601
		dab2008c01v1ModuleGroup OBJECT-GROUP
			OBJECTS {dab2008c01v1Index, dab2008c01v1ActivePreset, dab2008c01v1LoadPreset, dab2008c01v1SavePreset, dab2008c01v1ManNAuto, 
				dab2008c01v1BaseSlot, dab2008c01v1SlotUsed, dab2008c01v1OvldLevel, dab2008c01v1BusSyncFail, dab2008c01v1BusSyncFailTrapEnable, 
				dab2008c01v1BusSyncUnlck, dab2008c01v1BusSyncUnlckTrapEnable, dab2008c01v1BusAudFail, dab2008c01v1BusAudFailTrapEnable, dab2008c01v1BusAudError, 
				dab2008c01v1BusAudErrorTrapEnable, dab2008c01v1AudClipEr, dab2008c01v1AudClipErTrapEnable, dab2008c01v1AudPresFail, dab2008c01v1AudPresFailTrapEnable, 
				dab2008c01v1AudOvldFail, dab2008c01v1AudOvldFailTrapEnable, dab2008c01v1Slot1Pres, dab2008c01v1Slot2Pres, dab2008c01v1Slot3Pres, 
				dab2008c01v1Slot4Pres, dab2008c01v1Slot5Pres, dab2008c01v1Slot6Pres, dab2008c01v1Slot7Pres, dab2008c01v1Slot8Pres, 
				dab2008c01v1SerialNo }
			STATUS current
			DESCRIPTION
				"Module DAB2008C01V1 Group"
			::= { varGroups 497601 }

		-- 1.3.6.1.4.1.10106.2.3.1.497701
		ddb2008c01v1ModuleGroup OBJECT-GROUP
			OBJECTS {ddb2008c01v1Index, ddb2008c01v1ActivePreset, ddb2008c01v1LoadPreset, ddb2008c01v1SavePreset, ddb2008c01v1ManNAuto, 
				ddb2008c01v1AesInNOut, ddb2008c01v1BaseSlot, ddb2008c01v1SlotUsed, ddb2008c01v1OvldLevel, ddb2008c01v1Gain0, 
				ddb2008c01v1Phase0, ddb2008c01v1Gain1, ddb2008c01v1Phase1, ddb2008c01v1Gain2, ddb2008c01v1Phase2, 
				ddb2008c01v1Gain3, ddb2008c01v1Phase3, ddb2008c01v1Gain4, ddb2008c01v1Phase4, ddb2008c01v1Gain5, 
				ddb2008c01v1Phase5, ddb2008c01v1Gain6, ddb2008c01v1Phase6, ddb2008c01v1Gain7, ddb2008c01v1Phase7, 
				ddb2008c01v1Gain8, ddb2008c01v1Phase8, ddb2008c01v1Gain9, ddb2008c01v1Phase9, ddb2008c01v1Gain10, 
				ddb2008c01v1Phase10, ddb2008c01v1Gain11, ddb2008c01v1Phase11, ddb2008c01v1Gain12, ddb2008c01v1Phase12, 
				ddb2008c01v1Gain13, ddb2008c01v1Phase13, ddb2008c01v1Gain14, ddb2008c01v1Phase14, ddb2008c01v1Gain15, 
				ddb2008c01v1Phase15, ddb2008c01v1BusTimFail, ddb2008c01v1BusTimFailTrapEnable, ddb2008c01v1BusTimUnlck, ddb2008c01v1BusTimUnlckTrapEnable, 
				ddb2008c01v1BusAudFail, ddb2008c01v1BusAudFailTrapEnable, ddb2008c01v1BusAudError, ddb2008c01v1BusAudErrorTrapEnable, ddb2008c01v1AudClipEr, 
				ddb2008c01v1AudClipErTrapEnable, ddb2008c01v1AudPresFail, ddb2008c01v1AudPresFailTrapEnable, ddb2008c01v1AudInsFail, ddb2008c01v1AudInsFailTrapEnable, 
				ddb2008c01v1AudOvldEr, ddb2008c01v1AudOvldErTrapEnable, ddb2008c01v1Slot1Pres, ddb2008c01v1Slot2Pres, ddb2008c01v1Slot3Pres, 
				ddb2008c01v1Slot4Pres, ddb2008c01v1Slot5Pres, ddb2008c01v1Slot6Pres, ddb2008c01v1Slot7Pres, ddb2008c01v1Slot8Pres, 
				ddb2008c01v1Aes1Pres, ddb2008c01v1Aes2Pres, ddb2008c01v1Aes3Pres, ddb2008c01v1Aes4Pres, ddb2008c01v1Aes5Pres, 
				ddb2008c01v1Aes6Pres, ddb2008c01v1Aes7Pres, ddb2008c01v1Aes8Pres, ddb2008c01v1Aes1AsyncFail, ddb2008c01v1Aes2AsyncFail, 
				ddb2008c01v1Aes3AsyncFail, ddb2008c01v1Aes4AsyncFail, ddb2008c01v1Aes5AsyncFail, ddb2008c01v1Aes6AsyncFail, ddb2008c01v1Aes7AsyncFail, 
				ddb2008c01v1Aes8AsyncFail, ddb2008c01v1SerialNo }
			STATUS current
			DESCRIPTION
				"Module DDB2008C01V1 Group"
			::= { varGroups 497701 }

		-- 1.3.6.1.4.1.10106.2.3.1.514901
		smc2000c01v1ModuleGroup OBJECT-GROUP
			OBJECTS {smc2000c01v1Index, smc2000c01v1P1EthMode, smc2000c01v1P2EthMode, smc2000c01v1PoEthMode, smc2000c01v1SfpPres, 
				smc2000c01v1SfpPresTrapEnable, smc2000c01v1SfpFail, smc2000c01v1SfpFailTrapEnable, smc2000c01v1SfpLos, smc2000c01v1SfpLosTrapEnable, 
				smc2000c01v1SfpDiagSupport, smc2000c01v1P1Status, smc2000c01v1P1StatusTrapEnable, smc2000c01v1P2Status, smc2000c01v1P2StatusTrapEnable, 
				smc2000c01v1PoStatus, smc2000c01v1PoStatusTrapEnable, smc2000c01v1SfpPower, smc2000c01v1SfpTemp, smc2000c01v1SerialNo }
			STATUS current
			DESCRIPTION
				"Module SMC2000C01V1 Group"
			::= { varGroups 514901 }

		-- 1.3.6.1.4.1.10106.2.3.1.517501
		gps2000c01v1ModuleGroup OBJECT-GROUP
			OBJECTS {gps2000c01v1Index, gps2000c01v1SyncMode, gps2000c01v1PtpSrvEnable, gps2000c01v1PtpCliEnable, gps2000c01v1InfoTimePps, 
				gps2000c01v1CableDelay, gps2000c01v1PtpDelayAsym, gps2000c01v1HoldoverTout, gps2000c01v1FTimeDriftEst, gps2000c01v1FTempDriftEst, 
				gps2000c01v1Longitude, gps2000c01v1Latitude, gps2000c01v1Altitude, gps2000c01v1IpAdd0, gps2000c01v1IpAdd1, 
				gps2000c01v1IpAdd2, gps2000c01v1IpAdd3, gps2000c01v1IpMask0, gps2000c01v1IpMask1, gps2000c01v1IpMask2, 
				gps2000c01v1IpMask3, gps2000c01v1IpGway0, gps2000c01v1IpGway1, gps2000c01v1IpGway2, gps2000c01v1IpGway3, 
				gps2000c01v1Profile, gps2000c01v1DelayMechanism, gps2000c01v1Priority1, gps2000c01v1Priority2, gps2000c01v1DomainNumber, 
				gps2000c01v1LogAnnounceInt, gps2000c01v1LogSyncInt, gps2000c01v1LogMinDRInt, gps2000c01v1LogMinPdRInt, gps2000c01v1AnnounceRTout, 
				gps2000c01v1ClockClass, gps2000c01v1PtpState, gps2000c01v1GnssLos, gps2000c01v1GnssLosTrapEnable, gps2000c01v1GnssPpsLos, 
				gps2000c01v1GnssPpsLosTrapEnable, gps2000c01v1GnssUnlock, gps2000c01v1GnssUnlockTrapEnable, gps2000c01v1GnssPpsErr, gps2000c01v1GnssPpsErrTrapEnable, 
				gps2000c01v1PtpLos, gps2000c01v1PtpLosTrapEnable, gps2000c01v1PtpPpsLos, gps2000c01v1PtpPpsLosTrapEnable, gps2000c01v1PtpUnlock, 
				gps2000c01v1PtpUnlockTrapEnable, gps2000c01v1PtpPpsErr, gps2000c01v1PtpPpsErrTrapEnable, gps2000c01v1SyncState, gps2000c01v1SyncStateTrapEnable, 
				gps2000c01v1ValidPps, gps2000c01v1ValidPpsTrapEnable, gps2000c01v1ModuleActive, gps2000c01v1ModuleActiveTrapEnable, gps2000c01v1RedSyncState, 
				gps2000c01v1RedSyncStateTrapEnable, gps2000c01v1RedModule, gps2000c01v1RedModuleTrapEnable, gps2000c01v1FixMode, gps2000c01v1FixModeTrapEnable, 
				gps2000c01v1DiffMode, gps2000c01v1NumUsedSats, gps2000c01v1CN0Max, gps2000c01v1PositionAcc, gps2000c01v1TimTosOffset, 
				gps2000c01v1SurveyTout, gps2000c01v1HoldoverTime, gps2000c01v1PowerStat, gps2000c01v1PowerStatTrapEnable, gps2000c01v1AntennaStat, 
				gps2000c01v1AntennaStatTrapEnable, gps2000c01v1EthLink, gps2000c01v1EthLinkTrapEnable, gps2000c01v1AdjustingFreq, gps2000c01v1OcxoWarInProg, 
				gps2000c01v1OnePpsStat, gps2000c01v1OnePpsStatTrapEnable, gps2000c01v1OnePps, gps2000c01v1GnssDelay, gps2000c01v1PtpDelay, 
				gps2000c01v1SerialNo, gps2000c01v1IpNtpSrv0, gps2000c01v1IpNtpSrv1, gps2000c01v1IpNtpSrv2, gps2000c01v1IpNtpSrv3, 
				gps2000c01v1TimeDateOk }
			STATUS current
			DESCRIPTION
				"Module GPS2000C01V1 Group"
			::= { varGroups 517501 }

		-- 1.3.6.1.4.1.10106.2.3.1.520301
		isw3000c01v1ModuleGroup OBJECT-GROUP
			OBJECTS {isw3000c01v1Index, isw3000c01v1Mode, isw3000c01v1ModeTrapEnable, isw3000c01v1DvbTMode, isw3000c01v1DvbTModeTrapEnable, 
				isw3000c01v1NarrowPllBw, isw3000c01v1Buzzer, isw3000c01v1NullPckRtp, isw3000c01v1EnSeamNondvbt, isw3000c01v1Input, 
				isw3000c01v1InputTrapEnable, isw3000c01v1InputStChange, isw3000c01v1InputChange, isw3000c01v1OutDelay, isw3000c01v1OutDelayTrapEnable, 
				isw3000c01v1AsiMainPrior, isw3000c01v1AsiMainPriorTrapEnable, isw3000c01v1AsiResPrior, isw3000c01v1AsiResPriorTrapEnable, isw3000c01v1StatReset, 
				isw3000c01v1StatSel, isw3000c01v1StatMode, isw3000c01v1IgmpVersion, isw3000c01v1EthMode, isw3000c01v1PingEnable, 
				isw3000c01v1PacketDelay, isw3000c01v1PacketDelayTrapEnable, isw3000c01v1IpLinkFailEn, isw3000c01v1IpDestFailEn, isw3000c01v1TsSyncLossEn, 
				isw3000c01v1SyncByErrorEn, isw3000c01v1PatErrorEn, isw3000c01v1CcErrorEn, isw3000c01v1PmtErrorEn, isw3000c01v1PidErrorEn, 
				isw3000c01v1PidErrorTime, isw3000c01v1Ch1Selection, isw3000c01v1Ch1SelectionTrapEnable, isw3000c01v1Ch2Selection, isw3000c01v1Ch2SelectionTrapEnable, 
				isw3000c01v1OutDelay0, isw3000c01v1OutDelay0TrapEnable, isw3000c01v1OutDelay1, isw3000c01v1OutDelay1TrapEnable, isw3000c01v1Str1UipDAdd3, 
				isw3000c01v1Str1UipDAdd2, isw3000c01v1Str1UipDAdd1, isw3000c01v1Str1UipDAdd0, isw3000c01v1Str1MipDAdd3, isw3000c01v1Str1MipDAdd2, 
				isw3000c01v1Str1MipDAdd1, isw3000c01v1Str1MipDAdd0, isw3000c01v1Str1DPortMsb, isw3000c01v1Str1DPortLsb, isw3000c01v1Str1FecEna, 
				isw3000c01v1Str1MulticEna, isw3000c01v1VlanRx1Enable, isw3000c01v1VlanRx1Reg1, isw3000c01v1VlanRx1Reg2, isw3000c01v1Str2UipDAdd3, 
				isw3000c01v1Str2UipDAdd2, isw3000c01v1Str2UipDAdd1, isw3000c01v1Str2UipDAdd0, isw3000c01v1Str2MipDAdd3, isw3000c01v1Str2MipDAdd2, 
				isw3000c01v1Str2MipDAdd1, isw3000c01v1Str2MipDAdd0, isw3000c01v1Str2DPortMsb, isw3000c01v1Str2DPortLsb, isw3000c01v1Str2FecEna, 
				isw3000c01v1Str2MulticEna, isw3000c01v1VlanRx2Enable, isw3000c01v1VlanRx2Reg1, isw3000c01v1VlanRx2Reg2, isw3000c01v1TxUniEna, 
				isw3000c01v1TxMultiEna, isw3000c01v1LocalIpAdd3, isw3000c01v1LocalIpAdd2, isw3000c01v1LocalIpAdd1, isw3000c01v1LocalIpAdd0, 
				isw3000c01v1LocalIpMask3, isw3000c01v1LocalIpMask2, isw3000c01v1LocalIpMask1, isw3000c01v1LocalIpMask0, isw3000c01v1LocalIpGway3, 
				isw3000c01v1LocalIpGway2, isw3000c01v1LocalIpGway1, isw3000c01v1LocalIpGway0, isw3000c01v1TxUipAdd3, isw3000c01v1TxUipAdd2, 
				isw3000c01v1TxUipAdd1, isw3000c01v1TxUipAdd0, isw3000c01v1TxMipAdd3, isw3000c01v1TxMipAdd2, isw3000c01v1TxMipAdd1, 
				isw3000c01v1TxMipAdd0, isw3000c01v1TxSPortMsb, isw3000c01v1TxSPortLsb, isw3000c01v1TxDPortMsb, isw3000c01v1TxDPortLsb, 
				isw3000c01v1VlanTxEnable, isw3000c01v1VlanTxPriority, isw3000c01v1VlanTxReg1, isw3000c01v1VlanTxReg2, isw3000c01v1TxLParam, 
				isw3000c01v1TxFecMode, isw3000c01v1TxDParam, isw3000c01v1TxTspkInIppk, isw3000c01v1TxRowDelay, isw3000c01v1TxColDelay, 
				isw3000c01v1LowCost, isw3000c01v1HighReliabilty, isw3000c01v1HighThroughput, isw3000c01v1LowDelay, isw3000c01v1Precedence, 
				isw3000c01v1Ttl, isw3000c01v1Str1IgmFAdd3, isw3000c01v1Str1IgmFAdd2, isw3000c01v1Str1IgmFAdd1, isw3000c01v1Str1IgmFAdd0, 
				isw3000c01v1Str2IgmFAdd3, isw3000c01v1Str2IgmFAdd2, isw3000c01v1Str2IgmFAdd1, isw3000c01v1Str2IgmFAdd0, isw3000c01v1DvbT2Lock1, 
				isw3000c01v1DvbT2Lock1TrapEnable, isw3000c01v1DvbT2Lock2, isw3000c01v1DvbT2Lock2TrapEnable, isw3000c01v1Ts1DelayExt, isw3000c01v1Ts2DelayExt, 
				isw3000c01v1DelayT20S, isw3000c01v1DelayT20Ms, isw3000c01v1DelayT21S, isw3000c01v1DelayT21Ms, isw3000c01v1Bitrate1, 
				isw3000c01v1Bitrate2, isw3000c01v11ppsFail, isw3000c01v11ppsFailTrapEnable, isw3000c01v110mhzFail, isw3000c01v110mhzFailTrapEnable, 
				isw3000c01v1OutputFail, isw3000c01v1OutputFailTrapEnable, isw3000c01v1Ts1DelWar, isw3000c01v1Ts1DelWarTrapEnable, isw3000c01v1Ts2DelWar, 
				isw3000c01v1Ts2DelWarTrapEnable, isw3000c01v1ExtFail1, isw3000c01v1ExtFail1TrapEnable, isw3000c01v1ExtFail2, isw3000c01v1ExtFail2TrapEnable, 
				isw3000c01v1GlobalSeam, isw3000c01v1GlobalSeamTrapEnable, isw3000c01v1SyncLossErr1, isw3000c01v1SyncLossErr1TrapEnable, isw3000c01v1SyncByteErr1, 
				isw3000c01v1SyncByteErr1TrapEnable, isw3000c01v1PatError1, isw3000c01v1PatError1TrapEnable, isw3000c01v1CcError1, isw3000c01v1CcError1TrapEnable, 
				isw3000c01v1PmtError1, isw3000c01v1PmtError1TrapEnable, isw3000c01v1PidError1, isw3000c01v1PidError1TrapEnable, isw3000c01v1MipError1, 
				isw3000c01v1MipError1TrapEnable, isw3000c01v1GlobalError1, isw3000c01v1GlobalError1TrapEnable, isw3000c01v1SyncLossErr2, isw3000c01v1SyncLossErr2TrapEnable, 
				isw3000c01v1SyncByteErr2, isw3000c01v1SyncByteErr2TrapEnable, isw3000c01v1PatError2, isw3000c01v1PatError2TrapEnable, isw3000c01v1CcError2, 
				isw3000c01v1CcError2TrapEnable, isw3000c01v1PmtError2, isw3000c01v1PmtError2TrapEnable, isw3000c01v1PidError2, isw3000c01v1PidError2TrapEnable, 
				isw3000c01v1MipError2, isw3000c01v1MipError2TrapEnable, isw3000c01v1GlobalError2, isw3000c01v1GlobalError2TrapEnable, isw3000c01v1IpRxAddress3, 
				isw3000c01v1IpRxAddress2, isw3000c01v1IpRxAddress1, isw3000c01v1IpRxAddress0, isw3000c01v1IpRxPort, isw3000c01v1LParam, 
				isw3000c01v1FecMode, isw3000c01v1PacketSize, isw3000c01v1DParam, isw3000c01v1TsPckInIpPck, isw3000c01v1PacketRate, 
				isw3000c01v1TimeSinceReset, isw3000c01v1LostIpPck, isw3000c01v1RecoveredIpPck, isw3000c01v1OutOrdIpPck, isw3000c01v1FecRate, 
				isw3000c01v1Link, isw3000c01v1System, isw3000c01v1DestAvailable, isw3000c01v1Ts1BufOvf, isw3000c01v1Ts2BufOvf, 
				isw3000c01v1Ts1BufUnd, isw3000c01v1Ts2BufUnd, isw3000c01v1BufferStatus, isw3000c01v1PingStatus, isw3000c01v1SerialNo, 
				isw3000c01v1SpeedForce, isw3000c01v1BadCrcPck, isw3000c01v1MaxBitrateNull, isw3000c01v1MinBitrateNull, isw3000c01v1PckNullMax, 
				isw3000c01v1PckNullMin, isw3000c01v1BitrateNull1, isw3000c01v1BitrateNull2, isw3000c01v1Ts1PckNull, isw3000c01v1Ts2PckNull, 
				isw3000c01v1BitrateErrorEn, isw3000c01v1NullPckErrEn, isw3000c01v1Ts1TraffFail, isw3000c01v1Ts1TraffFailTrapEnable, isw3000c01v1Ts1NullPFail, 
				isw3000c01v1Ts1NullPFailTrapEnable, isw3000c01v1Ts2TraffFail, isw3000c01v1Ts2TraffFailTrapEnable, isw3000c01v1Ts2NullPFail, isw3000c01v1Ts2NullPFailTrapEnable, 
				isw3000c01v1PidSyncMode, isw3000c01v1PidSync, isw3000c01v1GlobalError1G, isw3000c01v1GlobalError2G, isw3000c01v1LeapSecRd0, 
				isw3000c01v1LeapSecRd1, isw3000c01v1MaxTimeOut, isw3000c01v1OutDelayT2, isw3000c01v1OutDelayT2TrapEnable, isw3000c01v1PatErrorTime, 
				isw3000c01v1PmtErrorTime, isw3000c01v1MaxDelayTxIp, isw3000c01v1InpFailMode }
			STATUS current
			DESCRIPTION
				"Module ISW3000C01V1 Group"
			::= { varGroups 520301 }

		-- 1.3.6.1.4.1.10106.2.3.1.520302
		isw3000c01v2ModuleGroup OBJECT-GROUP
			OBJECTS {isw3000c01v2Index, isw3000c01v2Mode, isw3000c01v2ModeTrapEnable, isw3000c01v2DvbTMode, isw3000c01v2DvbTModeTrapEnable, 
				isw3000c01v2NarrowPllBw, isw3000c01v2Buzzer, isw3000c01v2NullPckRtp, isw3000c01v2EnSeamNondvbt, isw3000c01v2Input, 
				isw3000c01v2InputTrapEnable, isw3000c01v2InputStChange, isw3000c01v2InputChange, isw3000c01v2OutDelay, isw3000c01v2OutDelayTrapEnable, 
				isw3000c01v2AsiMainPrior, isw3000c01v2AsiMainPriorTrapEnable, isw3000c01v2AsiResPrior, isw3000c01v2AsiResPriorTrapEnable, isw3000c01v2StatReset, 
				isw3000c01v2StatSel, isw3000c01v2StatMode, isw3000c01v2IgmpVersion, isw3000c01v2EthMode, isw3000c01v2PingEnable, 
				isw3000c01v2SpeedForce, isw3000c01v2OutDelayT2, isw3000c01v2OutDelayT2TrapEnable, isw3000c01v2PacketDelay, isw3000c01v2PacketDelayTrapEnable, 
				isw3000c01v2IpLinkFailEn, isw3000c01v2IpDestFailEn, isw3000c01v2TsSyncLossEn, isw3000c01v2SyncByErrorEn, isw3000c01v2PatErrorEn, 
				isw3000c01v2CcErrorEn, isw3000c01v2PmtErrorEn, isw3000c01v2PidErrorEn, isw3000c01v2BitrateErrorEn, isw3000c01v2NullPckErrEn, 
				isw3000c01v2PidErrorTime, isw3000c01v2Ch1Selection, isw3000c01v2Ch1SelectionTrapEnable, isw3000c01v2Ch2Selection, isw3000c01v2Ch2SelectionTrapEnable, 
				isw3000c01v2MaxTimeOut, isw3000c01v2OutDelay0, isw3000c01v2OutDelay0TrapEnable, isw3000c01v2OutDelay1, isw3000c01v2OutDelay1TrapEnable, 
				isw3000c01v2PidSyncMode, isw3000c01v2PidSync, isw3000c01v2PatErrorTime, isw3000c01v2PmtErrorTime, isw3000c01v2Str1UipDAdd3, 
				isw3000c01v2Str1UipDAdd2, isw3000c01v2Str1UipDAdd1, isw3000c01v2Str1UipDAdd0, isw3000c01v2Str1MipDAdd3, isw3000c01v2Str1MipDAdd2, 
				isw3000c01v2Str1MipDAdd1, isw3000c01v2Str1MipDAdd0, isw3000c01v2Str1DPortMsb, isw3000c01v2Str1DPortLsb, isw3000c01v2Str1FecEna, 
				isw3000c01v2Str1MulticEna, isw3000c01v2VlanRx1Enable, isw3000c01v2VlanRx1Reg1, isw3000c01v2VlanRx1Reg2, isw3000c01v2Str2UipDAdd3, 
				isw3000c01v2Str2UipDAdd2, isw3000c01v2Str2UipDAdd1, isw3000c01v2Str2UipDAdd0, isw3000c01v2Str2MipDAdd3, isw3000c01v2Str2MipDAdd2, 
				isw3000c01v2Str2MipDAdd1, isw3000c01v2Str2MipDAdd0, isw3000c01v2Str2DPortMsb, isw3000c01v2Str2DPortLsb, isw3000c01v2Str2FecEna, 
				isw3000c01v2Str2MulticEna, isw3000c01v2VlanRx2Enable, isw3000c01v2VlanRx2Reg1, isw3000c01v2VlanRx2Reg2, isw3000c01v2TxUniEna, 
				isw3000c01v2TxMultiEna, isw3000c01v2LocalIpAdd3, isw3000c01v2LocalIpAdd2, isw3000c01v2LocalIpAdd1, isw3000c01v2LocalIpAdd0, 
				isw3000c01v2LocalIpMask3, isw3000c01v2LocalIpMask2, isw3000c01v2LocalIpMask1, isw3000c01v2LocalIpMask0, isw3000c01v2LocalIpGway3, 
				isw3000c01v2LocalIpGway2, isw3000c01v2LocalIpGway1, isw3000c01v2LocalIpGway0, isw3000c01v2TxUipAdd3, isw3000c01v2TxUipAdd2, 
				isw3000c01v2TxUipAdd1, isw3000c01v2TxUipAdd0, isw3000c01v2TxMipAdd3, isw3000c01v2TxMipAdd2, isw3000c01v2TxMipAdd1, 
				isw3000c01v2TxMipAdd0, isw3000c01v2TxSPortMsb, isw3000c01v2TxSPortLsb, isw3000c01v2TxDPortMsb, isw3000c01v2TxDPortLsb, 
				isw3000c01v2VlanTxEnable, isw3000c01v2VlanTxPriority, isw3000c01v2VlanTxReg1, isw3000c01v2VlanTxReg2, isw3000c01v2TxLParam, 
				isw3000c01v2TxFecMode, isw3000c01v2TxDParam, isw3000c01v2TxTspkInIppk, isw3000c01v2TxRowDelay, isw3000c01v2TxColDelay, 
				isw3000c01v2LowCost, isw3000c01v2HighReliabilty, isw3000c01v2HighThroughput, isw3000c01v2LowDelay, isw3000c01v2Precedence, 
				isw3000c01v2Ttl, isw3000c01v2Str1IgmFAdd3, isw3000c01v2Str1IgmFAdd2, isw3000c01v2Str1IgmFAdd1, isw3000c01v2Str1IgmFAdd0, 
				isw3000c01v2Str2IgmFAdd3, isw3000c01v2Str2IgmFAdd2, isw3000c01v2Str2IgmFAdd1, isw3000c01v2Str2IgmFAdd0, isw3000c01v2MaxBitrateNull, 
				isw3000c01v2MinBitrateNull, isw3000c01v2PckNullMax, isw3000c01v2PckNullMin, isw3000c01v2DvbT2Lock1, isw3000c01v2DvbT2Lock1TrapEnable, 
				isw3000c01v2DvbT2Lock2, isw3000c01v2DvbT2Lock2TrapEnable, isw3000c01v2Ts1DelayExt, isw3000c01v2Ts2DelayExt, isw3000c01v2DelayT20S, 
				isw3000c01v2DelayT20Ms, isw3000c01v2DelayT21S, isw3000c01v2DelayT21Ms, isw3000c01v2Bitrate1, isw3000c01v2Bitrate2, 
				isw3000c01v2BitrateNull1, isw3000c01v2BitrateNull2, isw3000c01v2Ts1PckNull, isw3000c01v2Ts2PckNull, isw3000c01v2Ts1TraffFail, 
				isw3000c01v2Ts1TraffFailTrapEnable, isw3000c01v2Ts1NullPFail, isw3000c01v2Ts1NullPFailTrapEnable, isw3000c01v2Ts2TraffFail, isw3000c01v2Ts2TraffFailTrapEnable, 
				isw3000c01v2Ts2NullPFail, isw3000c01v2Ts2NullPFailTrapEnable, isw3000c01v21ppsFail, isw3000c01v21ppsFailTrapEnable, isw3000c01v210mhzFail, 
				isw3000c01v210mhzFailTrapEnable, isw3000c01v2OutputFail, isw3000c01v2OutputFailTrapEnable, isw3000c01v2Ts1DelWar, isw3000c01v2Ts1DelWarTrapEnable, 
				isw3000c01v2Ts2DelWar, isw3000c01v2Ts2DelWarTrapEnable, isw3000c01v2ExtFail1, isw3000c01v2ExtFail1TrapEnable, isw3000c01v2ExtFail2, 
				isw3000c01v2ExtFail2TrapEnable, isw3000c01v2GlobalSeam, isw3000c01v2GlobalSeamTrapEnable, isw3000c01v2SyncLossErr1, isw3000c01v2SyncLossErr1TrapEnable, 
				isw3000c01v2SyncByteErr1, isw3000c01v2SyncByteErr1TrapEnable, isw3000c01v2PatError1, isw3000c01v2PatError1TrapEnable, isw3000c01v2CcError1, 
				isw3000c01v2CcError1TrapEnable, isw3000c01v2PmtError1, isw3000c01v2PmtError1TrapEnable, isw3000c01v2PidError1, isw3000c01v2PidError1TrapEnable, 
				isw3000c01v2MipError1, isw3000c01v2MipError1TrapEnable, isw3000c01v2GlobalError1, isw3000c01v2GlobalError1TrapEnable, isw3000c01v2GlobalError1G, 
				isw3000c01v2SyncLossErr2, isw3000c01v2SyncLossErr2TrapEnable, isw3000c01v2SyncByteErr2, isw3000c01v2SyncByteErr2TrapEnable, isw3000c01v2PatError2, 
				isw3000c01v2PatError2TrapEnable, isw3000c01v2CcError2, isw3000c01v2CcError2TrapEnable, isw3000c01v2PmtError2, isw3000c01v2PmtError2TrapEnable, 
				isw3000c01v2PidError2, isw3000c01v2PidError2TrapEnable, isw3000c01v2MipError2, isw3000c01v2MipError2TrapEnable, isw3000c01v2GlobalError2, 
				isw3000c01v2GlobalError2TrapEnable, isw3000c01v2GlobalError2G, isw3000c01v2IpRxAddress3, isw3000c01v2IpRxAddress2, isw3000c01v2IpRxAddress1, 
				isw3000c01v2IpRxAddress0, isw3000c01v2IpRxPort, isw3000c01v2LParam, isw3000c01v2FecMode, isw3000c01v2PacketSize, 
				isw3000c01v2DParam, isw3000c01v2TsPckInIpPck, isw3000c01v2PacketRate, isw3000c01v2TimeSinceReset, isw3000c01v2LostIpPck, 
				isw3000c01v2RecoveredIpPck, isw3000c01v2BadCrcPck, isw3000c01v2OutOrdIpPck, isw3000c01v2FecRate, isw3000c01v2Link, 
				isw3000c01v2System, isw3000c01v2DestAvailable, isw3000c01v2Ts1BufOvf, isw3000c01v2Ts2BufOvf, isw3000c01v2Ts1BufUnd, 
				isw3000c01v2Ts2BufUnd, isw3000c01v2BufferStatus, isw3000c01v2PingStatus, isw3000c01v2SerialNo, isw3000c01v2MaxDelayTxIp, 
				isw3000c01v2InpFailMode }
			STATUS current
			DESCRIPTION
				"Module ISW3000C01V2 Group"
			::= { varGroups 520302 }

		-- 1.3.6.1.4.1.10106.2.3.1.522601
		imb2000c01v1ModuleGroup OBJECT-GROUP
			OBJECTS {imb2000c01v1Index, imb2000c01v1SyncInterface, imb2000c01v1StatMode, imb2000c01v1StatReset, imb2000c01v1Aes67Enable, 
				imb2000c01v1TtlTx, imb2000c01v1TxSrPort, imb2000c01v1EthMode1, imb2000c01v1SpeedForce1, imb2000c01v1Address12En, 
				imb2000c01v1EthMode2, imb2000c01v1SpeedForce2, imb2000c01v1Address22En, imb2000c01v1LocalIpGway3, imb2000c01v1LocalIpGway2, 
				imb2000c01v1LocalIpGway1, imb2000c01v1LocalIpGway0, imb2000c01v1Slot1M2sIns, imb2000c01v1Slot2M2sIns, imb2000c01v1Slot3M2sIns, 
				imb2000c01v1Slot4M2sIns, imb2000c01v1Slot5M2sIns, imb2000c01v1Slot6M2sIns, imb2000c01v1Slot7M2sIns, imb2000c01v1Slot8M2sIns, 
				imb2000c01v1Profile, imb2000c01v1DomainNumber, imb2000c01v1LogAnnounceInt, imb2000c01v1LogSyncInt, imb2000c01v1LogMinDRInt, 
				imb2000c01v1StreamOk1, imb2000c01v1BufferUnderf1, imb2000c01v1BufferOverf1, imb2000c01v1MalformedPck1, imb2000c01v1RxFail1, 
				imb2000c01v1Rx1PckRate, imb2000c01v1Rx1LostIpPk, imb2000c01v1Rx1DupIpPck, imb2000c01v1MaxBuffLev1, imb2000c01v1MinBuffLev1, 
				imb2000c01v1StreamOk2, imb2000c01v1BufferUnderf2, imb2000c01v1BufferOverf2, imb2000c01v1MalformedPck2, imb2000c01v1RxFail2, 
				imb2000c01v1Rx2PckRate, imb2000c01v1Rx2LostIpPk, imb2000c01v1Rx2DupIpPck, imb2000c01v1MaxBuffLev2, imb2000c01v1MinBuffLev2, 
				imb2000c01v1StreamOk3, imb2000c01v1BufferUnderf3, imb2000c01v1BufferOverf3, imb2000c01v1MalformedPck3, imb2000c01v1RxFail3, 
				imb2000c01v1Rx3PckRate, imb2000c01v1Rx3LostIpPk, imb2000c01v1Rx3DupIpPck, imb2000c01v1MaxBuffLev3, imb2000c01v1MinBuffLev3, 
				imb2000c01v1StreamOk4, imb2000c01v1BufferUnderf4, imb2000c01v1BufferOverf4, imb2000c01v1MalformedPck4, imb2000c01v1RxFail4, 
				imb2000c01v1Rx4PckRate, imb2000c01v1Rx4LostIpPk, imb2000c01v1Rx4DupIpPck, imb2000c01v1MaxBuffLev4, imb2000c01v1MinBuffLev4, 
				imb2000c01v1StreamOk5, imb2000c01v1BufferUnderf5, imb2000c01v1BufferOverf5, imb2000c01v1MalformedPck5, imb2000c01v1RxFail5, 
				imb2000c01v1Rx5PckRate, imb2000c01v1Rx5LostIpPk, imb2000c01v1Rx5DupIpPck, imb2000c01v1MaxBuffLev5, imb2000c01v1MinBuffLev5, 
				imb2000c01v1StreamOk6, imb2000c01v1BufferUnderf6, imb2000c01v1BufferOverf6, imb2000c01v1MalformedPck6, imb2000c01v1RxFail6, 
				imb2000c01v1Rx6PckRate, imb2000c01v1Rx6LostIpPk, imb2000c01v1Rx6DupIpPck, imb2000c01v1MaxBuffLev6, imb2000c01v1MinBuffLev6, 
				imb2000c01v1StreamOk7, imb2000c01v1BufferUnderf7, imb2000c01v1BufferOverf7, imb2000c01v1MalformedPck7, imb2000c01v1RxFail7, 
				imb2000c01v1Rx7PckRate, imb2000c01v1Rx7LostIpPk, imb2000c01v1Rx7DupIpPck, imb2000c01v1MaxBuffLev7, imb2000c01v1MinBuffLev7, 
				imb2000c01v1StreamOk8, imb2000c01v1BufferUnderf8, imb2000c01v1BufferOverf8, imb2000c01v1MalformedPck8, imb2000c01v1RxFail8, 
				imb2000c01v1Rx8PckRate, imb2000c01v1Rx8LostIpPk, imb2000c01v1Rx8DupIpPck, imb2000c01v1MaxBuffLev8, imb2000c01v1MinBuffLev8, 
				imb2000c01v1StreamOk9, imb2000c01v1BufferUnderf9, imb2000c01v1BufferOverf9, imb2000c01v1MalformedPck9, imb2000c01v1RxFail9, 
				imb2000c01v1Rx9PckRate, imb2000c01v1Rx9LostIpPk, imb2000c01v1Rx9DupIpPck, imb2000c01v1MaxBuffLev9, imb2000c01v1MinBuffLev9, 
				imb2000c01v1StreamOk10, imb2000c01v1BufferUnderf10, imb2000c01v1BufferOverf10, imb2000c01v1MalformedPck10, imb2000c01v1RxFail10, 
				imb2000c01v1Rx10PckRate, imb2000c01v1Rx10LostIpPk, imb2000c01v1Rx10DupIpPck, imb2000c01v1MaxBuffLev10, imb2000c01v1MinBuffLev10, 
				imb2000c01v1StreamOk11, imb2000c01v1BufferUnderf11, imb2000c01v1BufferOverf11, imb2000c01v1MalformedPck11, imb2000c01v1RxFail11, 
				imb2000c01v1Rx11PckRate, imb2000c01v1Rx11LostIpPk, imb2000c01v1Rx11DupIpPck, imb2000c01v1MaxBuffLev11, imb2000c01v1MinBuffLev11, 
				imb2000c01v1StreamOk12, imb2000c01v1BufferUnderf12, imb2000c01v1BufferOverf12, imb2000c01v1MalformedPck12, imb2000c01v1RxFail12, 
				imb2000c01v1Rx12PckRate, imb2000c01v1Rx12LostIpPk, imb2000c01v1Rx12DupIpPck, imb2000c01v1MaxBuffLev12, imb2000c01v1MinBuffLev12, 
				imb2000c01v1StreamOk13, imb2000c01v1BufferUnderf13, imb2000c01v1BufferOverf13, imb2000c01v1MalformedPck13, imb2000c01v1RxFail13, 
				imb2000c01v1Rx13PckRate, imb2000c01v1Rx13LostIpPk, imb2000c01v1Rx13DupIpPck, imb2000c01v1MaxBuffLev13, imb2000c01v1MinBuffLev13, 
				imb2000c01v1StreamOk14, imb2000c01v1BufferUnderf14, imb2000c01v1BufferOverf14, imb2000c01v1MalformedPck14, imb2000c01v1RxFail14, 
				imb2000c01v1Rx14PckRate, imb2000c01v1Rx14LostIpPk, imb2000c01v1Rx14DupIpPck, imb2000c01v1MaxBuffLev14, imb2000c01v1MinBuffLev14, 
				imb2000c01v1StreamOk15, imb2000c01v1BufferUnderf15, imb2000c01v1BufferOverf15, imb2000c01v1MalformedPck15, imb2000c01v1RxFail15, 
				imb2000c01v1Rx15PckRate, imb2000c01v1Rx15LostIpPk, imb2000c01v1Rx15DupIpPck, imb2000c01v1MaxBuffLev15, imb2000c01v1MinBuffLev15, 
				imb2000c01v1StreamOk16, imb2000c01v1BufferUnderf16, imb2000c01v1BufferOverf16, imb2000c01v1MalformedPck16, imb2000c01v1RxFail16, 
				imb2000c01v1Rx16PckRate, imb2000c01v1Rx16LostIpPk, imb2000c01v1Rx16DupIpPck, imb2000c01v1MaxBuffLev16, imb2000c01v1MinBuffLev16, 
				imb2000c01v1EnWc48k, imb2000c01v1EnBusRefTx, imb2000c01v1Slot1S2mPres, imb2000c01v1Slot2S2mPres, imb2000c01v1Slot3S2mPres, 
				imb2000c01v1Slot4S2mPres, imb2000c01v1Slot5S2mPres, imb2000c01v1Slot6S2mPres, imb2000c01v1Slot7S2mPres, imb2000c01v1Slot8S2mPres, 
				imb2000c01v1BusRxFail, imb2000c01v1MadiTxNCh, imb2000c01v1ShufOk, imb2000c01v1LocalIp1Add3, imb2000c01v1LocalIp1Add2, 
				imb2000c01v1LocalIp1Add1, imb2000c01v1LocalIp1Add0, imb2000c01v1LocalIp1Msk3, imb2000c01v1LocalIp1Msk2, imb2000c01v1LocalIp1Msk1, 
				imb2000c01v1LocalIp1Msk0, imb2000c01v1Vlan1Enable, imb2000c01v1VlanPriority1, imb2000c01v1Vlan1Id, imb2000c01v1LocalIp2Add3, 
				imb2000c01v1LocalIp2Add2, imb2000c01v1LocalIp2Add1, imb2000c01v1LocalIp2Add0, imb2000c01v1LocalIp2Msk3, imb2000c01v1LocalIp2Msk2, 
				imb2000c01v1LocalIp2Msk1, imb2000c01v1LocalIp2Msk0, imb2000c01v1Vlan2Enable, imb2000c01v1VlanPriority2, imb2000c01v1Vlan2Id, 
				imb2000c01v1LocalIp3Add3, imb2000c01v1LocalIp3Add2, imb2000c01v1LocalIp3Add1, imb2000c01v1LocalIpAdd0, imb2000c01v1LocalIp3Msk3, 
				imb2000c01v1LocalIp3Msk2, imb2000c01v1LocalIp3Msk1, imb2000c01v1LocalIp3Msk0, imb2000c01v1Vlan3Enable, imb2000c01v1VlanPriority3, 
				imb2000c01v1Vlan3Id, imb2000c01v1LocalIp4Add3, imb2000c01v1LocalIp4Add2, imb2000c01v1LocalIp4Add1, imb2000c01v1LocalIp4Add0, 
				imb2000c01v1LocalIp4Msk3, imb2000c01v1LocalIp4Msk2, imb2000c01v1LocalIp4Msk1, imb2000c01v1LocalIp4Msk0, imb2000c01v1Vlan4Enable, 
				imb2000c01v1VlanPriority4, imb2000c01v1Vlan4Id, imb2000c01v1SysError, imb2000c01v1PtpIntSelected, imb2000c01v1TxWorkinStat1, 
				imb2000c01v1ArpValid1, imb2000c01v1IcmpError1, imb2000c01v1TxWorkinStat2, imb2000c01v1ArpValid2, imb2000c01v1IcmpError2, 
				imb2000c01v1TxWorkinStat3, imb2000c01v1ArpValid3, imb2000c01v1IcmpError3, imb2000c01v1TxWorkinStat4, imb2000c01v1ArpValid4, 
				imb2000c01v1IcmpError4, imb2000c01v1TxWorkinStat5, imb2000c01v1ArpValid5, imb2000c01v1IcmpError5, imb2000c01v1TxWorkinStat6, 
				imb2000c01v1ArpValid6, imb2000c01v1IcmpError6, imb2000c01v1TxWorkinStat7, imb2000c01v1ArpValid7, imb2000c01v1IcmpError7, 
				imb2000c01v1TxWorkinStat8, imb2000c01v1ArpValid8, imb2000c01v1IcmpError8, imb2000c01v1PtpState, imb2000c01v1MadiRxOk, 
				imb2000c01v1MadiRxNCh, imb2000c01v1ClkStatus, imb2000c01v1ClockOffset, imb2000c01v1ClockDelay, imb2000c01v1RxTimeRst, 
				imb2000c01v1Link1, imb2000c01v1System1, imb2000c01v1Link2, imb2000c01v1System2, imb2000c01v1SerialNo }
			STATUS current
			DESCRIPTION
				"Module IMB2000C01V1 Group"
			::= { varGroups 522601 }

		-- 1.3.6.1.4.1.10106.2.3.1.523601
		swc2000c01v1ModuleGroup OBJECT-GROUP
			OBJECTS {swc2000c01v1Index, swc2000c01v1Gpo1, swc2000c01v1Gpo2, swc2000c01v1Gpo3, swc2000c01v1Gpo4, 
				swc2000c01v1InvertGpi1Pol, swc2000c01v1InvertGpi2Pol, swc2000c01v1InvertGpi3Pol, swc2000c01v1InvertGpi4Pol, swc2000c01v1InvertGpo1Pol, 
				swc2000c01v1InvertGpo2Pol, swc2000c01v1InvertGpo3Pol, swc2000c01v1InvertGpo4Pol, swc2000c01v1Gpi1, swc2000c01v1Gpi1TrapEnable, 
				swc2000c01v1Gpi2, swc2000c01v1Gpi2TrapEnable, swc2000c01v1Gpi3, swc2000c01v1Gpi3TrapEnable, swc2000c01v1Gpi4, 
				swc2000c01v1Gpi4TrapEnable, swc2000c01v1RedBoard, swc2000c01v1RedBoardTrapEnable, swc2000c01v1EthLink, swc2000c01v1EthLinkTrapEnable, 
				swc2000c01v1EthRedAct, swc2000c01v1EthRedActTrapEnable, swc2000c01v1SerialNo }
			STATUS current
			DESCRIPTION
				"Module SWC2000C01V1 Group"
			::= { varGroups 523601 }

		-- 1.3.6.1.4.1.10106.2.3.1.524101
		psu2001c01v1ModuleGroup OBJECT-GROUP
			OBJECTS {psu2001c01v1Index, psu2001c01v1PowerOff, psu2001c01v1PowerOffTrapEnable, psu2001c01v1TempWarning, psu2001c01v1TempWarningTrapEnable, 
				psu2001c01v1TempFail, psu2001c01v1TempFailTrapEnable, psu2001c01v1PwrWarning, psu2001c01v1PwrWarningTrapEnable, psu2001c01v1PwrFail, 
				psu2001c01v1PwrFailTrapEnable, psu2001c01v1InputVolt, psu2001c01v1OutputPower, psu2001c01v1ActTemp, psu2001c01v1MeanTemp, 
				psu2001c01v1MaxTemp, psu2001c01v1PonHours, psu2001c01v1TotMaxTemp, psu2001c01v1TotPonHours, psu2001c01v1TotPonTimes, 
				psu2001c01v1SerialNo }
			STATUS current
			DESCRIPTION
				"Module PSU2001C01V1 Group"
			::= { varGroups 524101 }

		-- 1.3.6.1.4.1.10106.2.3.1.527201
		eol2000c01v1ModuleGroup OBJECT-GROUP
			OBJECTS {eol2000c01v1Index, eol2000c01v1GenlockMode, eol2000c01v1Format, eol2000c01v1Bits, eol2000c01v1DeleteGr1, 
				eol2000c01v1DeleteGr2, eol2000c01v1DeleteGr3, eol2000c01v1DeleteGr4, eol2000c01v1FreezeTout, eol2000c01v1InFormat1, 
				eol2000c01v1InFormat1TrapEnable, eol2000c01v1InFormat2, eol2000c01v1RefUnlock, eol2000c01v1RefUnlockTrapEnable, eol2000c01v1NoSigA, 
				eol2000c01v1NoSigATrapEnable, eol2000c01v1NoSigB, eol2000c01v1NoSigBTrapEnable, eol2000c01v1SfpPres, eol2000c01v1SfpPresTrapEnable, 
				eol2000c01v1FailPtnDet, eol2000c01v1Grp1PresA, eol2000c01v1Grp2PresA, eol2000c01v1Grp3PresA, eol2000c01v1Grp4PresA, 
				eol2000c01v1Grp1PresB, eol2000c01v1Grp2PresB, eol2000c01v1Grp3PresB, eol2000c01v1Grp4PresB, eol2000c01v1Grp1P0ErrA, 
				eol2000c01v1Grp1P1ErrA, eol2000c01v1Grp2P0ErrA, eol2000c01v1Grp2P1ErrA, eol2000c01v1Grp3P0ErrA, eol2000c01v1Grp3P1ErrA, 
				eol2000c01v1Grp4P0ErrA, eol2000c01v1Grp4P1ErrA, eol2000c01v1R2lIn1Pres, eol2000c01v1R2lIn2Pres, eol2000c01v1R2lIn3Pres, 
				eol2000c01v1R2lIn4Pres, eol2000c01v1R2lIn5Pres, eol2000c01v1R2lIn6Pres, eol2000c01v1R2lIn7Pres, eol2000c01v1R2lIn8Pres, 
				eol2000c01v1R2lIn9Pres, eol2000c01v1R2lIn10Pres, eol2000c01v1R2lIn11Pres, eol2000c01v1R2lIn12Pres, eol2000c01v1R2lIn13Pres, 
				eol2000c01v1R2lIn14Pres, eol2000c01v1R2lIn15Pres, eol2000c01v1R2lIn16Pres, eol2000c01v1EthLink, eol2000c01v1EthSystem, 
				eol2000c01v1Grp1P0ErrB, eol2000c01v1Grp1P1ErrB, eol2000c01v1Grp2P0ErrB, eol2000c01v1Grp2P1ErrB, eol2000c01v1Grp3P0ErrB, 
				eol2000c01v1Grp3P1ErrB, eol2000c01v1Grp4P0ErrB, eol2000c01v1Grp4P1ErrB, eol2000c01v1RxPower, eol2000c01v1SerialNo }
			STATUS current
			DESCRIPTION
				"Module EOL2000C01V1 Group"
			::= { varGroups 527201 }

		-- 1.3.6.1.4.1.10106.2.3.1.529001
		ttd2000c01v1ModuleGroup OBJECT-GROUP
			OBJECTS {ttd2000c01v1Index, ttd2000c01v1FrInput, ttd2000c01v1FrInputTrapEnable, ttd2000c01v1Onepps12, ttd2000c01v1Onepps12TrapEnable, 
				ttd2000c01v1Onepps34, ttd2000c01v1Onepps34TrapEnable, ttd2000c01v1Impedance, ttd2000c01v1ForceTtlOut, ttd2000c01v1FrFail, 
				ttd2000c01v1FrFailTrapEnable, ttd2000c01v1ReTtlFail, ttd2000c01v1ReTtlFailTrapEnable, ttd2000c01v1Re10mhzFail, ttd2000c01v1Re10mhzFailTrapEnable, 
				ttd2000c01v1SerialNo }
			STATUS current
			DESCRIPTION
				"Module TTD2000C01V1 Group"
			::= { varGroups 529001 }

		-- 1.3.6.1.4.1.10106.2.3.1.530801
		psu2100c01v1ModuleGroup OBJECT-GROUP
			OBJECTS {psu2100c01v1Index, psu2100c01v1PowerOff, psu2100c01v1PowerOffTrapEnable, psu2100c01v1TempWarning, psu2100c01v1TempWarningTrapEnable, 
				psu2100c01v1TempFail, psu2100c01v1TempFailTrapEnable, psu2100c01v1PwrWarning, psu2100c01v1PwrWarningTrapEnable, psu2100c01v1PwrFail, 
				psu2100c01v1PwrFailTrapEnable, psu2100c01v1InputVolt, psu2100c01v1OutputPower, psu2100c01v1ActTemp, psu2100c01v1MeanTemp, 
				psu2100c01v1MaxTemp, psu2100c01v1PonHours, psu2100c01v1TotMaxTemp, psu2100c01v1TotPonHours, psu2100c01v1TotPonTimes, 
				psu2100c01v1SerialNo }
			STATUS current
			DESCRIPTION
				"Module PSU2100C01V1 Group"
			::= { varGroups 530801 }

		-- 1.3.6.1.4.1.10106.2.3.1.538901
		atg2000c01v1ModuleGroup OBJECT-GROUP
			OBJECTS {atg2000c01v1Index, atg2000c01v1ActivePreset, atg2000c01v1LoadPreset, atg2000c01v1SavePreset, atg2000c01v1LtcFormat, 
				atg2000c01v1MuxSrc2, atg2000c01v1AudFr, atg2000c01v1AudDip, atg2000c01v1AudLev, atg2000c01v1SampRate, 
				atg2000c01v1DropFrame, atg2000c01v1Bgf, atg2000c01v1DateFormat, atg2000c01v1EnDateGen, atg2000c01v1SumMonthSt, 
				atg2000c01v1SumWeekSt, atg2000c01v1SumWDaySt, atg2000c01v1SumHourSt, atg2000c01v1SumHourOffset, atg2000c01v1WinMonthSt, 
				atg2000c01v1WinWeekSt, atg2000c01v1WinWDaySt, atg2000c01v1WinHourSt, atg2000c01v1WinHourOffset, atg2000c01v1EnDlsave, 
				atg2000c01v1RefLockFail, atg2000c01v1RefLockFailTrapEnable, atg2000c01v1TcFail, atg2000c01v1RefPresentFail, atg2000c01v1SerialNo }
			STATUS current
			DESCRIPTION
				"Module ATG2000C01V1 Group"
			::= { varGroups 538901 }

		-- 1.3.6.1.4.1.10106.2.3.1.540801
		hvd2001c01v1ModuleGroup OBJECT-GROUP
			OBJECTS {hvd2001c01v1Index, hvd2001c01v1NoSig, hvd2001c01v1NoSigTrapEnable, hvd2001c01v1Unlock, hvd2001c01v1UnlockTrapEnable, 
				hvd2001c01v1Hd, hvd2001c01v1SerialNo }
			STATUS current
			DESCRIPTION
				"Module HVD2001C01V1 Group"
			::= { varGroups 540801 }

		-- 1.3.6.1.4.1.10106.2.3.1.542501
		gti2000c01v1ModuleGroup OBJECT-GROUP
			OBJECTS {gti2000c01v1Index, gti2000c01v1ActivePreset, gti2000c01v1LoadPreset, gti2000c01v1SavePreset, gti2000c01v1Mode, 
				gti2000c01v1ModeTrapEnable, gti2000c01v1InputChgRst, gti2000c01v1Input, gti2000c01v1InputTrapEnable, gti2000c01v1InvertPriority, 
				gti2000c01v1MuteEn, gti2000c01v1TWait, gti2000c01v1TMute, gti2000c01v1RearFail, gti2000c01v1RearFailTrapEnable, 
				gti2000c01v1FrontFail, gti2000c01v1FrontFailTrapEnable, gti2000c01v1Unlock, gti2000c01v1UnlockTrapEnable, gti2000c01v1SerialNo }
			STATUS current
			DESCRIPTION
				"Module GTI2000C01V1 Group"
			::= { varGroups 542501 }

		-- 1.3.6.1.4.1.10106.2.3.1.550001
		ste2022c01v1ModuleGroup OBJECT-GROUP
			OBJECTS {ste2022c01v1Index, ste2022c01v1ActivePreset, ste2022c01v1LoadPreset, ste2022c01v1SavePreset, ste2022c01v1StatReset, 
				ste2022c01v1StatMode, ste2022c01v1InpFailMode, ste2022c01v1DirControl1, ste2022c01v1DirControl2, ste2022c01v1DirControl3, 
				ste2022c01v1DirControl4, ste2022c01v1FrBufferMod1, ste2022c01v1FrBufferMod2, ste2022c01v1FrBufferMod3, ste2022c01v1FrBufferMod4, 
				ste2022c01v1RefInput, ste2022c01v1ExpRefFormat, ste2022c01v1RefLckFailMsk, ste2022c01v1TimeOut, ste2022c01v1Tx1UniEna, 
				ste2022c01v1Tx1MultiEna, ste2022c01v1Tx1FecMode, ste2022c01v1TimestampCf1, ste2022c01v1Tx1UipAdd3, ste2022c01v1Tx1UipAdd2, 
				ste2022c01v1Tx1UipAdd1, ste2022c01v1Tx1UipAdd0, ste2022c01v1Tx1MipAdd3, ste2022c01v1Tx1MipAdd2, ste2022c01v1Tx1MipAdd1, 
				ste2022c01v1Tx1MipAdd0, ste2022c01v1Tx1SPort, ste2022c01v1Tx1DPort, ste2022c01v1Tx1LParam, ste2022c01v1Tx1DParam, 
				ste2022c01v1Tx1RowDelay, ste2022c01v1Tx1ColDelay, ste2022c01v1TxIp1SrAdd3, ste2022c01v1TxIp1SrAdd2, ste2022c01v1TxIp1SrAdd1, 
				ste2022c01v1TxIp1SrAdd0, ste2022c01v1TxIp1SrMsk0, ste2022c01v1TxIp1SrMsk1, ste2022c01v1TxIp1SrMsk2, ste2022c01v1TxIp1SrMsk3, 
				ste2022c01v1Tx2UniEna, ste2022c01v1Tx2MultiEna, ste2022c01v1Tx2FecMode, ste2022c01v1TimestampCf2, ste2022c01v1Tx2UipAdd3, 
				ste2022c01v1Tx2UipAdd2, ste2022c01v1Tx2UipAdd1, ste2022c01v1Tx2UipAdd0, ste2022c01v1Tx2MipAdd3, ste2022c01v1Tx2MipAdd2, 
				ste2022c01v1Tx2MipAdd1, ste2022c01v1Tx2MipAdd0, ste2022c01v1Tx2SPort, ste2022c01v1Tx2DPort, ste2022c01v1Tx2LParam, 
				ste2022c01v1Tx2DParam, ste2022c01v1Tx2RowDelay, ste2022c01v1Tx2ColDelay, ste2022c01v1TxIp2SrAdd3, ste2022c01v1TxIp2SrAdd2, 
				ste2022c01v1TxIp2SrAdd1, ste2022c01v1TxIp2SrAdd0, ste2022c01v1TxIp2SrMsk0, ste2022c01v1TxIp2SrMsk1, ste2022c01v1TxIp2SrMsk2, 
				ste2022c01v1TxIp2SrMsk3, ste2022c01v1Tx3UniEna, ste2022c01v1Tx3MultiEna, ste2022c01v1Tx3FecMode, ste2022c01v1TimestampCf3, 
				ste2022c01v1Tx3UipAdd3, ste2022c01v1Tx3UipAdd2, ste2022c01v1Tx3UipAdd1, ste2022c01v1Tx3UipAdd0, ste2022c01v1Tx3MipAdd3, 
				ste2022c01v1Tx3MipAdd2, ste2022c01v1Tx3MipAdd1, ste2022c01v1Tx3MipAdd0, ste2022c01v1Tx3SPort, ste2022c01v1Tx3DPort, 
				ste2022c01v1Tx3LParam, ste2022c01v1Tx3DParam, ste2022c01v1Tx3RowDelay, ste2022c01v1Tx3ColDelay, ste2022c01v1TxIp3SrAdd3, 
				ste2022c01v1TxIp3SrAdd2, ste2022c01v1TxIp3SrAdd1, ste2022c01v1TxIp3SrAdd0, ste2022c01v1TxIp3SrMsk3, ste2022c01v1TxIp3SrMsk2, 
				ste2022c01v1TxIp3SrMsk1, ste2022c01v1TxIp3SrMsk0, ste2022c01v1Tx4UniEna, ste2022c01v1Tx4MultiEna, ste2022c01v1Tx4FecMode, 
				ste2022c01v1TimestampCf4, ste2022c01v1Tx4UipAdd3, ste2022c01v1Tx4UipAdd2, ste2022c01v1Tx4UipAdd1, ste2022c01v1Tx4UipAdd0, 
				ste2022c01v1Tx4MipAdd3, ste2022c01v1Tx4MipAdd2, ste2022c01v1Tx4MipAdd1, ste2022c01v1Tx4MipAdd0, ste2022c01v1Tx4SPort, 
				ste2022c01v1Tx4DPort, ste2022c01v1Tx4LParam, ste2022c01v1Tx4DParam, ste2022c01v1Tx4RowDelay, ste2022c01v1Tx4ColDelay, 
				ste2022c01v1TxIp4SrAdd3, ste2022c01v1TxIp4SrAdd2, ste2022c01v1TxIp4SrAdd1, ste2022c01v1TxIp4SrAdd0, ste2022c01v1TxIp4SrMsk3, 
				ste2022c01v1TxIp4SrMsk2, ste2022c01v1TxIp4SrMsk1, ste2022c01v1TxIp4SrMsk0, ste2022c01v1Str1Ena, ste2022c01v1Str1MulticEna, 
				ste2022c01v1Str1FecEna, ste2022c01v1Str1UipDAdd3, ste2022c01v1Str1UipDAdd2, ste2022c01v1Str1UipDAdd1, ste2022c01v1Str1UipDAdd0, 
				ste2022c01v1Str1MipDAdd3, ste2022c01v1Str1MipDAdd2, ste2022c01v1Str1MipDAdd1, ste2022c01v1Str1MipDAdd0, ste2022c01v1Str1IgmFAdd3, 
				ste2022c01v1Str1IgmFAdd2, ste2022c01v1Str1IgmFAdd1, ste2022c01v1Str1IgmFAdd0, ste2022c01v1Str1DPort, ste2022c01v1RxIp1SrMsk, 
				ste2022c01v1RxIp1SrMsk2, ste2022c01v1RxIp1SrMsk1, ste2022c01v1RxIp1SrMsk0, ste2022c01v1Str2Ena, ste2022c01v1Str2MulticEna, 
				ste2022c01v1Str2FecEna, ste2022c01v1Str2UipDAdd3, ste2022c01v1Str2UipDAdd2, ste2022c01v1Str2UipDAdd1, ste2022c01v1Str2UipDAdd0, 
				ste2022c01v1Str2MipDAdd3, ste2022c01v1Str2MipDAdd2, ste2022c01v1Str2MipDAdd1, ste2022c01v1Str2MipDAdd0, ste2022c01v1Str2IgmFAdd3, 
				ste2022c01v1Str2IgmFAdd2, ste2022c01v1Str2IgmFAdd1, ste2022c01v1Str2IgmFAdd0, ste2022c01v1Str2DPort, ste2022c01v1RxIp2SrMsk, 
				ste2022c01v1RxIp2SrMsk1, ste2022c01v1RxIp2SrMsk2, ste2022c01v1RxIp2SrMsk3, ste2022c01v1Str3Ena, ste2022c01v1Str3MulticEna, 
				ste2022c01v1Str3FecEna, ste2022c01v1Str3UipDAdd3, ste2022c01v1Str3UipDAdd2, ste2022c01v1Str3UipDAdd1, ste2022c01v1Str3UipDAdd0, 
				ste2022c01v1Str3MipDAdd3, ste2022c01v1Str3MipDAdd2, ste2022c01v1Str3MipDAdd1, ste2022c01v1Str3MipDAdd0, ste2022c01v1Str3IgmFAdd3, 
				ste2022c01v1Str3IgmFAdd2, ste2022c01v1Str3IgmFAdd1, ste2022c01v1Str3IgmFAdd0, ste2022c01v1Str3DPort, ste2022c01v1RxIp3SrMsk3, 
				ste2022c01v1RxIp3SrMsk2, ste2022c01v1RxIp3SrMsk1, ste2022c01v1RxIp3SrMsk0, ste2022c01v1Str4Ena, ste2022c01v1Str4MulticEna, 
				ste2022c01v1Str4FecEna, ste2022c01v1Str4UipDAdd3, ste2022c01v1Str4UipDAdd2, ste2022c01v1Str4UipDAdd1, ste2022c01v1Str4UipDAdd0, 
				ste2022c01v1Str4MipDAdd3, ste2022c01v1Str4MipDAdd2, ste2022c01v1Str4MipDAdd1, ste2022c01v1Str4MipDAdd0, ste2022c01v1Str4IgmFAdd3, 
				ste2022c01v1Str4IgmFAdd2, ste2022c01v1Str4IgmFAdd1, ste2022c01v1Str4IgmFAdd0, ste2022c01v1Str4DPort, ste2022c01v1RxIp4SrMsk3, 
				ste2022c01v1RxIp4SrMsk2, ste2022c01v1RxIp4SrMsk1, ste2022c01v1RxIp4SrMsk0, ste2022c01v1Rx1FecMode, ste2022c01v1Rx1IpRxAdd3, 
				ste2022c01v1Rx1IpRxAdd2, ste2022c01v1Rx1IpRxAdd1, ste2022c01v1Rx1IpRxAdd0, ste2022c01v1Rx1IpRxPort, ste2022c01v1Rx1LParam, 
				ste2022c01v1Rx1DParam, ste2022c01v1Rx2FecMode, ste2022c01v1Rx2IpRxAdd3, ste2022c01v1Rx2IpRxAdd2, ste2022c01v1Rx2IpRxAdd1, 
				ste2022c01v1Rx2IpRxAdd0, ste2022c01v1Rx2IpRxPort, ste2022c01v1Rx2LParam, ste2022c01v1Rx2DParam, ste2022c01v1Rx3FecMode, 
				ste2022c01v1Rx3IpRxAdd3, ste2022c01v1Rx3IpRxAdd2, ste2022c01v1Rx3IpRxAdd1, ste2022c01v1Rx3IpRxAdd0, ste2022c01v1Rx3IpRxPort, 
				ste2022c01v1Rx3LParam, ste2022c01v1Rx3DParam, ste2022c01v1Rx4FecMode, ste2022c01v1Rx4IpRxAdd3, ste2022c01v1Rx4IpRxAdd2, 
				ste2022c01v1Rx4IpRxAdd1, ste2022c01v1Rx4IpRxAdd0, ste2022c01v1Rx4IpRxPort, ste2022c01v1Rx4LParam, ste2022c01v1Rx4DParam, 
				ste2022c01v1LocalIp2Add3, ste2022c01v1LocalIp2Add2, ste2022c01v1LocalIp2Add1, ste2022c01v1LocalIp2Add0, ste2022c01v1LocalIp2Msk3, 
				ste2022c01v1LocalIp2Msk2, ste2022c01v1LocalIp2Msk1, ste2022c01v1LocalIp2Msk0, ste2022c01v1LocalIpGway3, ste2022c01v1LocalIpGway2, 
				ste2022c01v1LocalIpGway1, ste2022c01v1LocalIpGway0, ste2022c01v1SysError, ste2022c01v1NoSignal1, ste2022c01v1NoSignal1Aux, 
				ste2022c01v1EdhCrc1, ste2022c01v1Format1, ste2022c01v1Format1Aux, ste2022c01v1NoSignal2, ste2022c01v1EdhCrc2, 
				ste2022c01v1Format2, ste2022c01v1NoSignal3, ste2022c01v1EdhCrc3, ste2022c01v1Format3, ste2022c01v1NoSignal4, 
				ste2022c01v1EdhCrc4, ste2022c01v1Format4, ste2022c01v1FormatIp1, ste2022c01v1RxIpFail1, ste2022c01v1LostLine1, 
				ste2022c01v1FormatIp2, ste2022c01v1RxIpFail2, ste2022c01v1LostLine2, ste2022c01v1FormatIp3, ste2022c01v1RxIpFail3, 
				ste2022c01v1LostLine3, ste2022c01v1FormatIp4, ste2022c01v1RxIpFail4, ste2022c01v1LostLine4, ste2022c01v1Link, 
				ste2022c01v1EthRemoteFault, ste2022c01v1EthTxActivity, ste2022c01v1EthRxActivity, ste2022c01v1ArpValid1, ste2022c01v1IcmpError1, 
				ste2022c01v1ArpValid2, ste2022c01v1IcmpError2, ste2022c01v1ArpValid3, ste2022c01v1IcmpError3, ste2022c01v1ArpValid4, 
				ste2022c01v1IcmpError4, ste2022c01v1RefLockFail, ste2022c01v1IntRefPres, ste2022c01v1GlobalStatus, ste2022c01v1SpeedStatus, 
				ste2022c01v1Temperature, ste2022c01v1SerialNo }
			STATUS current
			DESCRIPTION
				"Module STE2022C01V1 Group"
			::= { varGroups 550001 }

		-- 1.3.6.1.4.1.10106.2.3.1.552801
		tly2010c01v1ModuleGroup OBJECT-GROUP
			OBJECTS {tly2010c01v1Index, tly2010c01v1Gpo, tly2010c01v1GpoTrapEnable, tly2010c01v1VirtGpo, tly2010c01v1MasterBrdAdd, 
				tly2010c01v1VirtMode, tly2010c01v1PhyGpo, tly2010c01v1PhyGpoTrapEnable, tly2010c01v1SerialNo }
			STATUS current
			DESCRIPTION
				"Module TLY2010C01V1 Group"
			::= { varGroups 552801 }

		-- 1.3.6.1.4.1.10106.2.3.1.553101
		hli2000c01v1ModuleGroup OBJECT-GROUP
			OBJECTS {hli2000c01v1Index, hli2000c01v1ActivePreset, hli2000c01v1LoadPreset, hli2000c01v1SavePreset, hli2000c01v1EnaAud20Bit, 
				hli2000c01v1IpAdd0, hli2000c01v1IpAdd1, hli2000c01v1IpAdd2, hli2000c01v1IpAdd3, hli2000c01v1IpMask0, 
				hli2000c01v1IpMask1, hli2000c01v1IpMask2, hli2000c01v1IpMask3, hli2000c01v1IpGway0, hli2000c01v1IpGway1, 
				hli2000c01v1IpGway2, hli2000c01v1IpGway3, hli2000c01v1LogoRdy1, hli2000c01v1LogoRdy2, hli2000c01v1AudioRdy, 
				hli2000c01v1FadeDur, hli2000c01v1FadeGain, hli2000c01v1MixType, hli2000c01v1LayerEn1, hli2000c01v1LayerType1, 
				hli2000c01v1FadeDur1, hli2000c01v1FadeTop1, hli2000c01v1CrawlEnLogo1, hli2000c01v1CrawlPeriodic1, hli2000c01v1CrawlSpeed1, 
				hli2000c01v1CrawlTimeS1, hli2000c01v1CrawlTimeM1, hli2000c01v1CrawlTimeH1, hli2000c01v1EnLogo11, hli2000c01v1IdLogo11, 
				hli2000c01v1XoffLogo11, hli2000c01v1YoffLogo11, hli2000c01v1EnLogo21, hli2000c01v1IdLogo21, hli2000c01v1XoffLogo21, 
				hli2000c01v1YoffLogo21, hli2000c01v1EnLogo31, hli2000c01v1IdLogo31, hli2000c01v1XoffLogo31, hli2000c01v1YoffLogo31, 
				hli2000c01v1EnLogo41, hli2000c01v1IdLogo41, hli2000c01v1XoffLogo41, hli2000c01v1YoffLogo41, hli2000c01v1IdLogoAnim1, 
				hli2000c01v1XoffLogoAnim1, hli2000c01v1YoffLogoAnim1, hli2000c01v1AniLogoType1, hli2000c01v1LayerEn2, hli2000c01v1LayerType2, 
				hli2000c01v1FadeDur2, hli2000c01v1FadeTop2, hli2000c01v1CrawlEnLogo2, hli2000c01v1CrawlPeriodic2, hli2000c01v1CrawlSpeed2, 
				hli2000c01v1CrawlTimeS2, hli2000c01v1CrawlTimeM2, hli2000c01v1CrawlTimeH2, hli2000c01v1EnLogo12, hli2000c01v1IdLogo12, 
				hli2000c01v1XoffLogo12, hli2000c01v1YoffLogo12, hli2000c01v1EnLogo22, hli2000c01v1IdLogo22, hli2000c01v1XoffLogo22, 
				hli2000c01v1YoffLogo22, hli2000c01v1EnLogo32, hli2000c01v1IdLogo32, hli2000c01v1XoffLogo32, hli2000c01v1YoffLogo32, 
				hli2000c01v1EnLogo42, hli2000c01v1IdLogo42, hli2000c01v1XoffLogo42, hli2000c01v1YoffLogo42, hli2000c01v1IdLogoAnim2, 
				hli2000c01v1XoffLogoAnim2, hli2000c01v1YoffLogoAnim2, hli2000c01v1AniLogoType2, hli2000c01v1IdLogoAud1, hli2000c01v1EnLogoAud1, 
				hli2000c01v1DstLogoAud1, hli2000c01v1Loop1, hli2000c01v1IdLogoAud2, hli2000c01v1EnLogoAud2, hli2000c01v1DstLogoAud2, 
				hli2000c01v1Loop2, hli2000c01v1IdLogoAud3, hli2000c01v1EnLogoAud3, hli2000c01v1DstLogoAud3, hli2000c01v1Loop3, 
				hli2000c01v1IdLogoAud4, hli2000c01v1EnLogoAud4, hli2000c01v1DstLogoAud4, hli2000c01v1Loop4, hli2000c01v1SubsOutlEn1, 
				hli2000c01v1SubsOutlEn2, hli2000c01v1HideVid1, hli2000c01v1HideVid2, hli2000c01v1SubsPage1, hli2000c01v1SubsPage2, 
				hli2000c01v1SubsOpacity1, hli2000c01v1SubsOpacity2, hli2000c01v1SubsSizeOff1, hli2000c01v1SubsSizeOff2, hli2000c01v1TtxPage1, 
				hli2000c01v1TtxPage2, hli2000c01v1RxFormat, hli2000c01v1RxFormatTrapEnable, hli2000c01v1VidValid, hli2000c01v1NoSignal, 
				hli2000c01v1NoSignalTrapEnable, hli2000c01v1EdhCrc, hli2000c01v1EdhCrcTrapEnable, hli2000c01v1LockFail, hli2000c01v1LockFailTrapEnable, 
				hli2000c01v1Gpi1, hli2000c01v1Gpi2, hli2000c01v1FailTtx1, hli2000c01v1FailTtx2, hli2000c01v1Grp1Pres, 
				hli2000c01v1Grp2Pres, hli2000c01v1Grp3Pres, hli2000c01v1Grp4Pres, hli2000c01v1EthLink, hli2000c01v1EthSystem, 
				hli2000c01v1SerialNo, hli2000c01v1ClockFormat, hli2000c01v1ClockAmPm, hli2000c01v1ClockSize, hli2000c01v1ClockEn, 
				hli2000c01v1ClockPosition, hli2000c01v1TcSource, hli2000c01v1AtcFail, hli2000c01v1DvitcFail, hli2000c01v1InputFPresSel }
			STATUS current
			DESCRIPTION
				"Module HLI2000C01V1 Group"
			::= { varGroups 553101 }

		-- 1.3.6.1.4.1.10106.2.3.1.553901
		vct2000c01v1ModuleGroup OBJECT-GROUP
			OBJECTS {vct2000c01v1Index, vct2000c01v1Mode, vct2000c01v1ModeTrapEnable, vct2000c01v1Buzzer, vct2000c01v1Input, 
				vct2000c01v1InputTrapEnable, vct2000c01v1InputChange, vct2000c01v1ActTime, vct2000c01v1RecTime, vct2000c01v1InpMainFail, 
				vct2000c01v1InpMainFailTrapEnable, vct2000c01v1GpiMainFail, vct2000c01v1GpiMainFailTrapEnable, vct2000c01v1InpResFail, vct2000c01v1InpResFailTrapEnable, 
				vct2000c01v1GpiResFail, vct2000c01v1GpiResFailTrapEnable, vct2000c01v1Gpo1, vct2000c01v1Gpo2, vct2000c01v1SerialNo }
			STATUS current
			DESCRIPTION
				"Module VCT2000C01V1 Group"
			::= { varGroups 553901 }

		-- 1.3.6.1.4.1.10106.2.3.1.554501
		hxc2000c01v1ModuleGroup OBJECT-GROUP
			OBJECTS {hxc2000c01v1Index, hxc2000c01v1ActivePreset, hxc2000c01v1LoadPreset, hxc2000c01v1SavePreset, hxc2000c01v1AnaRefFmt, 
				hxc2000c01v1AnaRefFmtTrapEnable, hxc2000c01v1GenlockMode, hxc2000c01v1EnaAud20Bit, hxc2000c01v1FailMode, hxc2000c01v1ModeConv, 
				hxc2000c01v1ModeConvTrapEnable, hxc2000c01v1OutAfd, hxc2000c01v1OutAfdTrapEnable, hxc2000c01v1OutCf, hxc2000c01v1OutCfTrapEnable, 
				hxc2000c01v1Esc11, hxc2000c01v1InAfdExpct, hxc2000c01v1InAfdExpctTrapEnable, hxc2000c01v1InCfExpct, hxc2000c01v1InCfExpctTrapEnable, 
				hxc2000c01v1TxFmt, hxc2000c01v1TxFmtTrapEnable, hxc2000c01v1DeintAlgorithm, hxc2000c01v1DeintAlgorithmTrapEnable, hxc2000c01v1OutEnaS2016, 
				hxc2000c01v1OutEnaVii, hxc2000c01v1OutEnaWss, hxc2000c01v1OutEnaVitc, hxc2000c01v1OutEnaAtc, hxc2000c01v1OutEnaTxt, 
				hxc2000c01v1OutEnaCea608, hxc2000c01v1SelAudPair0, hxc2000c01v1SelAudPair1, hxc2000c01v1SelAudPair2, hxc2000c01v1SelAudPair3, 
				hxc2000c01v1SelAudPair4, hxc2000c01v1SelAudPair5, hxc2000c01v1SelAudPair6, hxc2000c01v1SelAudPair7, hxc2000c01v1VDelay, 
				hxc2000c01v1HDelay, hxc2000c01v1Grp1P0Gain, hxc2000c01v1Grp1P0Phase, hxc2000c01v1Grp1P1Gain, hxc2000c01v1Grp1P1Phase, 
				hxc2000c01v1Grp2P0Gain, hxc2000c01v1Grp2P0Phase, hxc2000c01v1Grp2P1Gain, hxc2000c01v1Grp2P1Phase, hxc2000c01v1Grp3P0Gain, 
				hxc2000c01v1Grp3P0Phase, hxc2000c01v1Grp3P1Gain, hxc2000c01v1Grp3P1Phase, hxc2000c01v1Grp4P0Gain, hxc2000c01v1Grp4P0Phase, 
				hxc2000c01v1Grp4P1Gain, hxc2000c01v1Grp4P1Phase, hxc2000c01v1StatFlash, hxc2000c01v1InPhyFail, hxc2000c01v1InPhyFailTrapEnable, 
				hxc2000c01v1InFmtFail, hxc2000c01v1InFmtFailTrapEnable, hxc2000c01v1InIncFail, hxc2000c01v1InIncFailTrapEnable, hxc2000c01v1InPresCrcFail, 
				hxc2000c01v1InCrcFail, hxc2000c01v1InCrcFailTrapEnable, hxc2000c01v1InPrsS352Fail, hxc2000c01v1InS352Fail, hxc2000c01v1PresS2016Fail, 
				hxc2000c01v1ErrS2016Fail, hxc2000c01v1PresAudG1Fail, hxc2000c01v1PresAudG1FailTrapEnable, hxc2000c01v1PresAudG2Fail, hxc2000c01v1PresAudG2FailTrapEnable, 
				hxc2000c01v1PresAudG3Fail, hxc2000c01v1PresAudG3FailTrapEnable, hxc2000c01v1PresAudG4Fail, hxc2000c01v1PresAudG4FailTrapEnable, hxc2000c01v1RefFail, 
				hxc2000c01v1RefFailTrapEnable, hxc2000c01v1RefFmtFail, hxc2000c01v1RefFmtFailTrapEnable, hxc2000c01v1LockFail, hxc2000c01v1LockFailTrapEnable, 
				hxc2000c01v1AudPair0Fail, hxc2000c01v1AudPair0FailTrapEnable, hxc2000c01v1AudPair1Fail, hxc2000c01v1AudPair1FailTrapEnable, hxc2000c01v1AudPair2Fail, 
				hxc2000c01v1AudPair2FailTrapEnable, hxc2000c01v1AudPair3Fail, hxc2000c01v1AudPair3FailTrapEnable, hxc2000c01v1AudPair4Fail, hxc2000c01v1AudPair4FailTrapEnable, 
				hxc2000c01v1AudPair5Fail, hxc2000c01v1AudPair5FailTrapEnable, hxc2000c01v1AudPair6Fail, hxc2000c01v1AudPair6FailTrapEnable, hxc2000c01v1AudPair7Fail, 
				hxc2000c01v1AudPair7FailTrapEnable, hxc2000c01v1InAfdDetct, hxc2000c01v1InAfdDetctTrapEnable, hxc2000c01v1InCfDetct, hxc2000c01v1InCfDetctTrapEnable, 
				hxc2000c01v1InFormat, hxc2000c01v1InFormatTrapEnable, hxc2000c01v1RefFormat, hxc2000c01v1RefFormatTrapEnable, hxc2000c01v1TxFormat, 
				hxc2000c01v1TxFormatTrapEnable, hxc2000c01v1TxtPres, hxc2000c01v1VitcPres, hxc2000c01v1Mute, hxc2000c01v1Black, 
				hxc2000c01v1Gpi1, hxc2000c01v1Gpi2, hxc2000c01v1Gpi3, hxc2000c01v1Gpi4, hxc2000c01v1SerialNo, 
				hxc2000c01v1MuteEna }
			STATUS current
			DESCRIPTION
				"Module HXC2000C01V1 Group"
			::= { varGroups 554501 }

		-- 1.3.6.1.4.1.10106.2.3.1.555601
		uop2000c01v1ModuleGroup OBJECT-GROUP
			OBJECTS {uop2000c01v1Index, uop2000c01v1InputA, uop2000c01v1InputATrapEnable, uop2000c01v1InputB, uop2000c01v1InputBTrapEnable, 
				uop2000c01v1BckTxEnA, uop2000c01v1BckTxEnB, uop2000c01v1ForceSfpType, uop2000c01v1ManualMode, uop2000c01v1LosA, 
				uop2000c01v1LosATrapEnable, uop2000c01v1UnlockA, uop2000c01v1UnlockATrapEnable, uop2000c01v1RateA, uop2000c01v1RateATrapEnable, 
				uop2000c01v1LosB, uop2000c01v1LosBTrapEnable, uop2000c01v1UnlockB, uop2000c01v1UnlockBTrapEnable, uop2000c01v1RateB, 
				uop2000c01v1RateBTrapEnable, uop2000c01v1SfpType, uop2000c01v1WavelengthA, uop2000c01v1WavelengthB, uop2000c01v1Temp, 
				uop2000c01v1PowerA, uop2000c01v1PowerB, uop2000c01v1SerialNo }
			STATUS current
			DESCRIPTION
				"Module UOP2000C01V1 Group"
			::= { varGroups 555601 }

		-- 1.3.6.1.4.1.10106.2.3.1.557901
		ur-2001r01v1ModuleGroup OBJECT-GROUP
			OBJECTS {ur-2001r01v1Index, ur-2001r01v1Psu0Fail, ur-2001r01v1Psu1Fail, ur-2001r01v1SerialNo }
			STATUS current
			DESCRIPTION
				"Module UR-2001R01V1 Group"
			::= { varGroups 557901 }

		-- 1.3.6.1.4.1.10106.2.3.1.574401
		act2000c01v1ModuleGroup OBJECT-GROUP
			OBJECTS {act2000c01v1Index, act2000c01v1Mode, act2000c01v1ModeTrapEnable, act2000c01v1Buzzer, act2000c01v1Input, 
				act2000c01v1InputTrapEnable, act2000c01v1InputChange, act2000c01v1AnaThrLev, act2000c01v1AesThrLev, act2000c01v1ActTime, 
				act2000c01v1RecTime, act2000c01v1InpMainFail, act2000c01v1InpMainFailTrapEnable, act2000c01v1GpiMainFail, act2000c01v1GpiMainFailTrapEnable, 
				act2000c01v1InpResFail, act2000c01v1InpResFailTrapEnable, act2000c01v1GpiResFail, act2000c01v1GpiResFailTrapEnable, act2000c01v1Gpo1, 
				act2000c01v1Gpo2, act2000c01v1AvgLevMain, act2000c01v1AvgLevRes, act2000c01v1PkLevMain, act2000c01v1PkLevRes, 
				act2000c01v1SerialNo }
			STATUS current
			DESCRIPTION
				"Module ACT2000C01V1 Group"
			::= { varGroups 574401 }

		-- 1.3.6.1.4.1.10106.2.3.1.577901
		utg2000c01v1ModuleGroup OBJECT-GROUP
			OBJECTS {utg2000c01v1Index, utg2000c01v1ActivePreset, utg2000c01v1LoadPreset, utg2000c01v1SavePreset, utg2000c01v1SdiRefInput, 
				utg2000c01v1OutputFormat, utg2000c01v1Pattern, utg2000c01v1RstErrors, utg2000c01v1ExpRefFormat, utg2000c01v1ExpRefFormatTrapEnable, 
				utg2000c01v1RefInput, utg2000c01v1RefInputTrapEnable, utg2000c01v1MeasInput, utg2000c01v1HDelay, utg2000c01v1VDelay, 
				utg2000c01v1AvDlyBlack, utg2000c01v1AvDlySil, utg2000c01v1OsdDlyEn, utg2000c01v1Pwm, utg2000c01v1OverlayIo1, 
				utg2000c01v1OverlayIo2, utg2000c01v1OverlayIo3, utg2000c01v1OverlayIo4, utg2000c01v1OverlayOptout, utg2000c01v1EnLogo11, 
				utg2000c01v1IdLogo11, utg2000c01v1XoffLogo11, utg2000c01v1YoffLogo11, utg2000c01v1EnLogo21, utg2000c01v1IdLogo21, 
				utg2000c01v1XoffLogo21, utg2000c01v1YoffLogo21, utg2000c01v1EnOsd1, utg2000c01v1Osd1Size, utg2000c01v1EnOsd2, 
				utg2000c01v1Osd2Size, utg2000c01v1Osd1MovEna, utg2000c01v1Osd1SpeedH, utg2000c01v1Osd1SpeedV, utg2000c01v1Osd1StartH, 
				utg2000c01v1Osd1StartV, utg2000c01v1Osd1EndH, utg2000c01v1Osd1EndV, utg2000c01v1EnAudIm1, utg2000c01v1EnAudIm2, 
				utg2000c01v1EnAudIm3, utg2000c01v1EnAudIm4, utg2000c01v1EnGrp1Aud0, utg2000c01v1EnGrp2Aud0, utg2000c01v1EnGrp3Aud0, 
				utg2000c01v1EnGrp4Aud0, utg2000c01v1VidDip0, utg2000c01v1AudFrP0G00, utg2000c01v1AudFrP1G00, utg2000c01v1AudFrP0G10, 
				utg2000c01v1AudFrP1G10, utg2000c01v1AudFrP0G20, utg2000c01v1AudFrP1G20, utg2000c01v1AudFrP0G30, utg2000c01v1AudFrP1G30, 
				utg2000c01v1AudDipP0G00, utg2000c01v1AudDipP1G00, utg2000c01v1AudDipP0G10, utg2000c01v1AudDipP1G10, utg2000c01v1AudDipP0G20, 
				utg2000c01v1AudDipP1G20, utg2000c01v1AudDipP0G30, utg2000c01v1AudDipP1G30, utg2000c01v1AudLevP0G00, utg2000c01v1AudLevP0G10, 
				utg2000c01v1AudLevP1G00, utg2000c01v1AudLevP1G10, utg2000c01v1AudLevP0G20, utg2000c01v1AudLevP1G20, utg2000c01v1AudLevP0G30, 
				utg2000c01v1AudLevP1G30, utg2000c01v1DropFrame, utg2000c01v1Bgf, utg2000c01v1DateFormat, utg2000c01v1EnDateGen, 
				utg2000c01v1AdjHourDay, utg2000c01v1SumMonthSt, utg2000c01v1SumWeekSt, utg2000c01v1SumWDaySt, utg2000c01v1SumHourSt, 
				utg2000c01v1SumHourOffset, utg2000c01v1WinMonthSt, utg2000c01v1WinWeekSt, utg2000c01v1WinWDaySt, utg2000c01v1WinHourSt, 
				utg2000c01v1WinHourOffset, utg2000c01v1EnDlsave, utg2000c01v1Delay1G1p0l, utg2000c01v1Delay1G1p0r, utg2000c01v1Delay1G1p1l, 
				utg2000c01v1Delay1G1p1r, utg2000c01v1Delay1G2p0l, utg2000c01v1Delay1G2p0r, utg2000c01v1Delay1G2p1l, utg2000c01v1Delay1G2p1r, 
				utg2000c01v1Delay1G3p0l, utg2000c01v1Delay1G3p0r, utg2000c01v1Delay1G3p1l, utg2000c01v1Delay1G3p1r, utg2000c01v1Delay1G4p0l, 
				utg2000c01v1Delay1G4p0r, utg2000c01v1Delay1G4p1l, utg2000c01v1Delay1G4p1r, utg2000c01v1Av1SeqG1p0, utg2000c01v1Av1SeqG1p1, 
				utg2000c01v1Av1SeqG2p0, utg2000c01v1Av1SeqG2p1, utg2000c01v1Av1SeqG3p0, utg2000c01v1Av1SeqG3p1, utg2000c01v1Av1SeqG4p0, 
				utg2000c01v1Av1SeqG4p1, utg2000c01v1Aud1GrpPres1, utg2000c01v1Aud1GrpPres2, utg2000c01v1Aud1GrpPres3, utg2000c01v1Aud1GrpPres4, 
				utg2000c01v1Av1SeqPhase, utg2000c01v1Delay2G1p0l, utg2000c01v1Delay2G1p0r, utg2000c01v1Delay2G1p1l, utg2000c01v1Delay2G1p1r, 
				utg2000c01v1Delay2G2p0l, utg2000c01v1Delay2G2p0r, utg2000c01v1Delay2G2p1l, utg2000c01v1Delay2G2p1r, utg2000c01v1Delay2G3p0l, 
				utg2000c01v1Delay2G3p0r, utg2000c01v1Delay2G3p1l, utg2000c01v1Delay2G3p1r, utg2000c01v1Delay2G4p0l, utg2000c01v1Delay2G4p0r, 
				utg2000c01v1Delay2G4p1l, utg2000c01v1Delay2G4p1r, utg2000c01v1Av2SeqG1p0, utg2000c01v1Av2SeqG1p1, utg2000c01v1Av2SeqG2p0, 
				utg2000c01v1Av2SeqG2p1, utg2000c01v1Av2SeqG3p0, utg2000c01v1Av2SeqG3p1, utg2000c01v1Av2SeqG4p0, utg2000c01v1Av2SeqG4p1, 
				utg2000c01v1Aud2GrpPres1, utg2000c01v1Aud2GrpPres2, utg2000c01v1Aud2GrpPres3, utg2000c01v1Aud2GrpPres4, utg2000c01v1Av2SeqPhase, 
				utg2000c01v1Delay3G1p0l, utg2000c01v1Delay3G1p0r, utg2000c01v1Delay3G1p1l, utg2000c01v1Delay3G1p1r, utg2000c01v1Delay3G2p0l, 
				utg2000c01v1Delay3G2p0r, utg2000c01v1Delay3G2p1l, utg2000c01v1Delay3G2p1r, utg2000c01v1Delay3G3p0l, utg2000c01v1Delay3G3p0r, 
				utg2000c01v1Delay3G3p1l, utg2000c01v1Delay3G3p1r, utg2000c01v1Delay3G4p0l, utg2000c01v1Delay3G4p0r, utg2000c01v1Delay3G4p1l, 
				utg2000c01v1Delay3G4p1r, utg2000c01v1Av3SeqG1p0, utg2000c01v1Av3SeqG1p1, utg2000c01v1Av3SeqG2p0, utg2000c01v1Av3SeqG2p1, 
				utg2000c01v1Av3SeqG3p0, utg2000c01v1Av3SeqG3p1, utg2000c01v1Av3SeqG4p0, utg2000c01v1Av3SeqG4p1, utg2000c01v1Aud3GrpPres1, 
				utg2000c01v1Aud3GrpPres2, utg2000c01v1Aud3GrpPres3, utg2000c01v1Aud3GrpPres4, utg2000c01v1Av3SeqPhase, utg2000c01v1DelayG1p0l, 
				utg2000c01v1DelayG1p0r, utg2000c01v1DelayG1p1l, utg2000c01v1DelayG1p1r, utg2000c01v1DelayG2p0l, utg2000c01v1DelayG2p0r, 
				utg2000c01v1DelayG2p1l, utg2000c01v1DelayG2p1r, utg2000c01v1DelayG3p0l, utg2000c01v1DelayG3p0r, utg2000c01v1DelayG3p1l, 
				utg2000c01v1DelayG3p1r, utg2000c01v1DelayG4p0l, utg2000c01v1DelayG4p0r, utg2000c01v1DelayG4p1l, utg2000c01v1DelayG4p1r, 
				utg2000c01v1AvSeqG1p0, utg2000c01v1AvSeqG1p1, utg2000c01v1AvSeqG2p0, utg2000c01v1AvSeqG2p1, utg2000c01v1AvSeqG3p0, 
				utg2000c01v1AvSeqG3p1, utg2000c01v1AvSeqG4p0, utg2000c01v1AvSeqG4p1, utg2000c01v1AudGrpPres1, utg2000c01v1AudGrpPres2, 
				utg2000c01v1AudGrpPres3, utg2000c01v1AudGrpPres4, utg2000c01v1AvSeqPhase, utg2000c01v1ArefFail, utg2000c01v1ArefFailTrapEnable, 
				utg2000c01v1DrefFail, utg2000c01v1DrefFailTrapEnable, utg2000c01v1IrefFail, utg2000c01v1IrefFailTrapEnable, utg2000c01v1RefIncFail, 
				utg2000c01v1RefIncFailTrapEnable, utg2000c01v1RefLockFail, utg2000c01v1RefLockFailTrapEnable, utg2000c01v1DrefCrcFail, utg2000c01v1DrefCrcFailTrapEnable, 
				utg2000c01v1TcFail, utg2000c01v1LogoRdy1, utg2000c01v1ArefFormat, utg2000c01v1ArefFormatTrapEnable, utg2000c01v1DrefFormat, 
				utg2000c01v1DrefFormatTrapEnable, utg2000c01v1CrcErrors, utg2000c01v1InputFailures, utg2000c01v1MeasDelay, utg2000c01v1MeasFreq, 
				utg2000c01v1SfpType, utg2000c01v1SfpTemp, utg2000c01v1SfpRxPower, utg2000c01v1SerialNo }
			STATUS current
			DESCRIPTION
				"Module UTG2000C01V1 Group"
			::= { varGroups 577901 }

		-- 1.3.6.1.4.1.10106.2.3.1.579101
		hvd2002c01v1ModuleGroup OBJECT-GROUP
			OBJECTS {hvd2002c01v1Index, hvd2002c01v1InputSel, hvd2002c01v1Bck0Sel, hvd2002c01v1Bck1Sel, hvd2002c01v1NoSig, 
				hvd2002c01v1NoSigTrapEnable, hvd2002c01v1Unlock, hvd2002c01v1UnlockTrapEnable, hvd2002c01v1Hd, hvd2002c01v1SerialNo }
			STATUS current
			DESCRIPTION
				"Module HVD2002C01V1 Group"
			::= { varGroups 579101 }

		-- 1.3.6.1.4.1.10106.2.3.1.583701
		hfs2001c01v1ModuleGroup OBJECT-GROUP
			OBJECTS {hfs2001c01v1Index, hfs2001c01v1SynchroMode, hfs2001c01v1FailMode, hfs2001c01v1VbiMode, hfs2001c01v1DelayMode, 
				hfs2001c01v1HDelay, hfs2001c01v1VDelay, hfs2001c01v1Bits, hfs2001c01v1FrameDelay, hfs2001c01v1NoSig, 
				hfs2001c01v1NoSigTrapEnable, hfs2001c01v1Unlock, hfs2001c01v1UnlockTrapEnable, hfs2001c01v1EdhCrc, hfs2001c01v1EdhCrcTrapEnable, 
				hfs2001c01v1NoRef, hfs2001c01v1NoRefTrapEnable, hfs2001c01v1RefUnlock, hfs2001c01v1RefUnlockTrapEnable, hfs2001c01v1InputFormat, 
				hfs2001c01v1SdiFormat, hfs2001c01v1Grp1Pres, hfs2001c01v1Grp2Pres, hfs2001c01v1Grp3Pres, hfs2001c01v1Grp4Pres, 
				hfs2001c01v1Grp1P0Err, hfs2001c01v1Grp1P1Err, hfs2001c01v1Grp2P0Err, hfs2001c01v1Grp2P1Err, hfs2001c01v1Grp3P0Err, 
				hfs2001c01v1Grp3P1Err, hfs2001c01v1Grp4P0Err, hfs2001c01v1Grp4P1Err, hfs2001c01v1R2lIn1Pres, hfs2001c01v1R2lIn2Pres, 
				hfs2001c01v1R2lIn3Pres, hfs2001c01v1R2lIn4Pres, hfs2001c01v1R2lIn5Pres, hfs2001c01v1R2lIn6Pres, hfs2001c01v1R2lIn7Pres, 
				hfs2001c01v1R2lIn8Pres, hfs2001c01v1R2lIn9Pres, hfs2001c01v1R2lIn10Pres, hfs2001c01v1R2lIn11Pres, hfs2001c01v1R2lIn12Pres, 
				hfs2001c01v1R2lIn13Pres, hfs2001c01v1R2lIn14Pres, hfs2001c01v1R2lIn15Pres, hfs2001c01v1R2lIn16Pres, hfs2001c01v1SerialNo }
			STATUS current
			DESCRIPTION
				"Module HFS2001C01V1 Group"
			::= { varGroups 583701 }

		-- 1.3.6.1.4.1.10106.2.3.1.586701
		gps3003c01v1ModuleGroup OBJECT-GROUP
			OBJECTS {gps3003c01v1Index, gps3003c01v1SyncMode, gps3003c01v1PtpSrvEnable, gps3003c01v1PtpCliEnable, gps3003c01v1InfoTimePps, 
				gps3003c01v1PtpDelayAsym, gps3003c01v1HoldoverTout, gps3003c01v1CableDelay, gps3003c01v1FTimeDriftEst, gps3003c01v1FTempDriftEst, 
				gps3003c01v1Longitude, gps3003c01v1Latitude, gps3003c01v1Altitude, gps3003c01v1IpAdd0, gps3003c01v1IpAdd1, 
				gps3003c01v1IpAdd2, gps3003c01v1IpAdd3, gps3003c01v1IpMask0, gps3003c01v1IpMask1, gps3003c01v1IpMask2, 
				gps3003c01v1IpMask3, gps3003c01v1IpGway0, gps3003c01v1IpGway1, gps3003c01v1IpGway2, gps3003c01v1IpGway3, 
				gps3003c01v1Profile, gps3003c01v1DelayMechanism, gps3003c01v1Priority1, gps3003c01v1Priority2, gps3003c01v1DomainNumber, 
				gps3003c01v1LogAnnounceInt, gps3003c01v1LogSyncInt, gps3003c01v1LogMinDRInt, gps3003c01v1LogMinPdRInt, gps3003c01v1AnnounceRTout, 
				gps3003c01v1ClockClass, gps3003c01v1PtpState, gps3003c01v1GnssLos, gps3003c01v1GnssLosTrapEnable, gps3003c01v1GnssPpsLos, 
				gps3003c01v1GnssPpsLosTrapEnable, gps3003c01v1GnssUnlock, gps3003c01v1GnssUnlockTrapEnable, gps3003c01v1GnssPpsErr, gps3003c01v1GnssPpsErrTrapEnable, 
				gps3003c01v1PtpLos, gps3003c01v1PtpLosTrapEnable, gps3003c01v1PtpPpsLos, gps3003c01v1PtpPpsLosTrapEnable, gps3003c01v1PtpUnlock, 
				gps3003c01v1PtpUnlockTrapEnable, gps3003c01v1PtpPpsErr, gps3003c01v1PtpPpsErrTrapEnable, gps3003c01v1SyncState, gps3003c01v1SyncStateTrapEnable, 
				gps3003c01v1ValidPps, gps3003c01v1ValidPpsTrapEnable, gps3003c01v1ModuleActive, gps3003c01v1ModuleActiveTrapEnable, gps3003c01v1RedSyncState, 
				gps3003c01v1RedSyncStateTrapEnable, gps3003c01v1RedModule, gps3003c01v1RedModuleTrapEnable, gps3003c01v1FixMode, gps3003c01v1FixModeTrapEnable, 
				gps3003c01v1DiffMode, gps3003c01v1NumUsedSats, gps3003c01v1CN0Max, gps3003c01v1PositionAcc, gps3003c01v1TimTosOffset, 
				gps3003c01v1SurveyTout, gps3003c01v1HoldoverTime, gps3003c01v1PowerStat, gps3003c01v1PowerStatTrapEnable, gps3003c01v1AntennaStat, 
				gps3003c01v1AntennaStatTrapEnable, gps3003c01v1EthLink, gps3003c01v1EthLinkTrapEnable, gps3003c01v1AdjustingFreq, gps3003c01v1OcxoWarInProg, 
				gps3003c01v1OnePpsStat, gps3003c01v1OnePpsStatTrapEnable, gps3003c01v1OnePps, gps3003c01v1GnssDelay, gps3003c01v1PtpDelay, 
				gps3003c01v1SerialNo, gps3003c01v1GnssModVer, gps3003c01v1IpNtpSrv0, gps3003c01v1IpNtpSrv1, gps3003c01v1IpNtpSrv2, 
				gps3003c01v1IpNtpSrv3, gps3003c01v1TimeDateOk }
			STATUS current
			DESCRIPTION
				"Module GPS3003C01V1 Group"
			::= { varGroups 586701 }

		-- 1.3.6.1.4.1.10106.2.3.1.586801
		sem2000c01v1ModuleGroup OBJECT-GROUP
			OBJECTS {sem2000c01v1Index, sem2000c01v1P1EthMode, sem2000c01v1P2EthMode, sem2000c01v1PoEthMode, sem2000c01v1NoRefQl, 
				sem2000c01v1SfpPres, sem2000c01v1SfpPresTrapEnable, sem2000c01v1SfpFail, sem2000c01v1SfpFailTrapEnable, sem2000c01v1SfpLos, 
				sem2000c01v1SfpLosTrapEnable, sem2000c01v1SfpDiagSupport, sem2000c01v1P1Status, sem2000c01v1P1StatusTrapEnable, sem2000c01v1P2Status, 
				sem2000c01v1P2StatusTrapEnable, sem2000c01v1PoStatus, sem2000c01v1PoStatusTrapEnable, sem2000c01v1SfpPower, sem2000c01v1SfpTemp, 
				sem2000c01v1BusUnlock, sem2000c01v1BusUnlockTrapEnable, sem2000c01v1BusLos, sem2000c01v1BusLosTrapEnable, sem2000c01v1SerialNo }
			STATUS current
			DESCRIPTION
				"Module SEM2000C01V1 Group"
			::= { varGroups 586801 }

		-- 1.3.6.1.4.1.10106.2.3.1.587301
		gps3003c02v1ModuleGroup OBJECT-GROUP
			OBJECTS {gps3003c02v1Index, gps3003c02v1SyncMode, gps3003c02v1PtpSrvEnable, gps3003c02v1PtpCliEnable, gps3003c02v1InfoTimePps, 
				gps3003c02v1PtpDelayAsym, gps3003c02v1HoldoverTout, gps3003c02v1CableDelay, gps3003c02v1FTimeDriftEst, gps3003c02v1FTempDriftEst, 
				gps3003c02v1Longitude, gps3003c02v1Latitude, gps3003c02v1Altitude, gps3003c02v1IpAdd0, gps3003c02v1IpAdd1, 
				gps3003c02v1IpAdd2, gps3003c02v1IpAdd3, gps3003c02v1IpMask0, gps3003c02v1IpMask1, gps3003c02v1IpMask2, 
				gps3003c02v1IpMask3, gps3003c02v1IpGway0, gps3003c02v1IpGway1, gps3003c02v1IpGway2, gps3003c02v1IpGway3, 
				gps3003c02v1Profile, gps3003c02v1DelayMechanism, gps3003c02v1Priority1, gps3003c02v1Priority2, gps3003c02v1DomainNumber, 
				gps3003c02v1LogAnnounceInt, gps3003c02v1LogSyncInt, gps3003c02v1LogMinDRInt, gps3003c02v1LogMinPdRInt, gps3003c02v1AnnounceRTout, 
				gps3003c02v1ClockClass, gps3003c02v1PtpState, gps3003c02v1GnssLos, gps3003c02v1GnssLosTrapEnable, gps3003c02v1GnssPpsLos, 
				gps3003c02v1GnssPpsLosTrapEnable, gps3003c02v1GnssUnlock, gps3003c02v1GnssUnlockTrapEnable, gps3003c02v1GnssPpsErr, gps3003c02v1GnssPpsErrTrapEnable, 
				gps3003c02v1PtpLos, gps3003c02v1PtpLosTrapEnable, gps3003c02v1PtpPpsLos, gps3003c02v1PtpPpsLosTrapEnable, gps3003c02v1PtpUnlock, 
				gps3003c02v1PtpUnlockTrapEnable, gps3003c02v1PtpPpsErr, gps3003c02v1PtpPpsErrTrapEnable, gps3003c02v1SyncState, gps3003c02v1SyncStateTrapEnable, 
				gps3003c02v1ValidPps, gps3003c02v1ValidPpsTrapEnable, gps3003c02v1ModuleActive, gps3003c02v1ModuleActiveTrapEnable, gps3003c02v1RedSyncState, 
				gps3003c02v1RedSyncStateTrapEnable, gps3003c02v1RedModule, gps3003c02v1RedModuleTrapEnable, gps3003c02v1FixMode, gps3003c02v1FixModeTrapEnable, 
				gps3003c02v1DiffMode, gps3003c02v1NumUsedSats, gps3003c02v1CN0Max, gps3003c02v1PositionAcc, gps3003c02v1TimTosOffset, 
				gps3003c02v1SurveyTout, gps3003c02v1HoldoverTime, gps3003c02v1PowerStat, gps3003c02v1PowerStatTrapEnable, gps3003c02v1AntennaStat, 
				gps3003c02v1AntennaStatTrapEnable, gps3003c02v1EthLink, gps3003c02v1EthLinkTrapEnable, gps3003c02v1AdjustingFreq, gps3003c02v1OcxoWarInProg, 
				gps3003c02v1OnePpsStat, gps3003c02v1OnePpsStatTrapEnable, gps3003c02v1OnePps, gps3003c02v1GnssDelay, gps3003c02v1PtpDelay, 
				gps3003c02v1SerialNo, gps3003c02v1GnssModVer, gps3003c02v1IpNtpSrv0, gps3003c02v1IpNtpSrv1, gps3003c02v1IpNtpSrv2, 
				gps3003c02v1IpNtpSrv3, gps3003c02v1TimeDateOk }
			STATUS current
			DESCRIPTION
				"Module GPS3003C02V1 Group"
			::= { varGroups 587301 }

		-- 1.3.6.1.4.1.10106.2.3.1.587501
		gps3003c03v1ModuleGroup OBJECT-GROUP
			OBJECTS {gps3003c03v1Index, gps3003c03v1SyncMode, gps3003c03v1PtpSrvEnable, gps3003c03v1PtpCliEnable, gps3003c03v1InfoTimePps, 
				gps3003c03v1PtpDelayAsym, gps3003c03v1HoldoverTout, gps3003c03v1CableDelay, gps3003c03v1FTimeDriftEst, gps3003c03v1FTempDriftEst, 
				gps3003c03v1Longitude, gps3003c03v1Latitude, gps3003c03v1Altitude, gps3003c03v1IpAdd0, gps3003c03v1IpAdd1, 
				gps3003c03v1IpAdd2, gps3003c03v1IpAdd3, gps3003c03v1IpMask0, gps3003c03v1IpMask1, gps3003c03v1IpMask2, 
				gps3003c03v1IpMask3, gps3003c03v1IpGway0, gps3003c03v1IpGway1, gps3003c03v1IpGway2, gps3003c03v1IpGway3, 
				gps3003c03v1Profile, gps3003c03v1DelayMechanism, gps3003c03v1Priority1, gps3003c03v1Priority2, gps3003c03v1DomainNumber, 
				gps3003c03v1LogAnnounceInt, gps3003c03v1LogSyncInt, gps3003c03v1LogMinDRInt, gps3003c03v1LogMinPdRInt, gps3003c03v1AnnounceRTout, 
				gps3003c03v1ClockClass, gps3003c03v1PtpState, gps3003c03v1GnssLos, gps3003c03v1GnssLosTrapEnable, gps3003c03v1GnssPpsLos, 
				gps3003c03v1GnssPpsLosTrapEnable, gps3003c03v1GnssUnlock, gps3003c03v1GnssUnlockTrapEnable, gps3003c03v1GnssPpsErr, gps3003c03v1GnssPpsErrTrapEnable, 
				gps3003c03v1PtpLos, gps3003c03v1PtpLosTrapEnable, gps3003c03v1PtpPpsLos, gps3003c03v1PtpPpsLosTrapEnable, gps3003c03v1PtpUnlock, 
				gps3003c03v1PtpUnlockTrapEnable, gps3003c03v1PtpPpsErr, gps3003c03v1PtpPpsErrTrapEnable, gps3003c03v1SyncState, gps3003c03v1SyncStateTrapEnable, 
				gps3003c03v1ValidPps, gps3003c03v1ValidPpsTrapEnable, gps3003c03v1ModuleActive, gps3003c03v1ModuleActiveTrapEnable, gps3003c03v1RedSyncState, 
				gps3003c03v1RedSyncStateTrapEnable, gps3003c03v1RedModule, gps3003c03v1RedModuleTrapEnable, gps3003c03v1FixMode, gps3003c03v1FixModeTrapEnable, 
				gps3003c03v1DiffMode, gps3003c03v1NumUsedSats, gps3003c03v1CN0Max, gps3003c03v1PositionAcc, gps3003c03v1TimTosOffset, 
				gps3003c03v1SurveyTout, gps3003c03v1HoldoverTime, gps3003c03v1PowerStat, gps3003c03v1PowerStatTrapEnable, gps3003c03v1AntennaStat, 
				gps3003c03v1AntennaStatTrapEnable, gps3003c03v1EthLink, gps3003c03v1EthLinkTrapEnable, gps3003c03v1AdjustingFreq, gps3003c03v1OcxoWarInProg, 
				gps3003c03v1OnePpsStat, gps3003c03v1OnePpsStatTrapEnable, gps3003c03v1OnePps, gps3003c03v1GnssDelay, gps3003c03v1PtpDelay, 
				gps3003c03v1SerialNo, gps3003c03v1GnssModVer, gps3003c03v1IpNtpSrv0, gps3003c03v1IpNtpSrv1, gps3003c03v1IpNtpSrv2, 
				gps3003c03v1IpNtpSrv3, gps3003c03v1TimeDateOk }
			STATUS current
			DESCRIPTION
				"Module GPS3003C03V1 Group"
			::= { varGroups 587501 }

		-- 1.3.6.1.4.1.10106.2.3.1.587701
		gps3003c04v1ModuleGroup OBJECT-GROUP
			OBJECTS {gps3003c04v1Index, gps3003c04v1SyncMode, gps3003c04v1PtpSrvEnable, gps3003c04v1PtpCliEnable, gps3003c04v1InfoTimePps, 
				gps3003c04v1PtpDelayAsym, gps3003c04v1HoldoverTout, gps3003c04v1CableDelay, gps3003c04v1FTimeDriftEst, gps3003c04v1FTempDriftEst, 
				gps3003c04v1Longitude, gps3003c04v1Latitude, gps3003c04v1Altitude, gps3003c04v1IpAdd0, gps3003c04v1IpAdd1, 
				gps3003c04v1IpAdd2, gps3003c04v1IpAdd3, gps3003c04v1IpMask0, gps3003c04v1IpMask1, gps3003c04v1IpMask2, 
				gps3003c04v1IpMask3, gps3003c04v1IpGway0, gps3003c04v1IpGway1, gps3003c04v1IpGway2, gps3003c04v1IpGway3, 
				gps3003c04v1Profile, gps3003c04v1DelayMechanism, gps3003c04v1Priority1, gps3003c04v1Priority2, gps3003c04v1DomainNumber, 
				gps3003c04v1LogAnnounceInt, gps3003c04v1LogSyncInt, gps3003c04v1LogMinDRInt, gps3003c04v1LogMinPdRInt, gps3003c04v1AnnounceRTout, 
				gps3003c04v1ClockClass, gps3003c04v1PtpState, gps3003c04v1GnssLos, gps3003c04v1GnssLosTrapEnable, gps3003c04v1GnssPpsLos, 
				gps3003c04v1GnssPpsLosTrapEnable, gps3003c04v1GnssUnlock, gps3003c04v1GnssUnlockTrapEnable, gps3003c04v1GnssPpsErr, gps3003c04v1GnssPpsErrTrapEnable, 
				gps3003c04v1PtpLos, gps3003c04v1PtpLosTrapEnable, gps3003c04v1PtpPpsLos, gps3003c04v1PtpPpsLosTrapEnable, gps3003c04v1PtpUnlock, 
				gps3003c04v1PtpUnlockTrapEnable, gps3003c04v1PtpPpsErr, gps3003c04v1PtpPpsErrTrapEnable, gps3003c04v1SyncState, gps3003c04v1SyncStateTrapEnable, 
				gps3003c04v1ValidPps, gps3003c04v1ValidPpsTrapEnable, gps3003c04v1ModuleActive, gps3003c04v1ModuleActiveTrapEnable, gps3003c04v1RedSyncState, 
				gps3003c04v1RedSyncStateTrapEnable, gps3003c04v1RedModule, gps3003c04v1RedModuleTrapEnable, gps3003c04v1FixMode, gps3003c04v1FixModeTrapEnable, 
				gps3003c04v1DiffMode, gps3003c04v1NumUsedSats, gps3003c04v1CN0Max, gps3003c04v1PositionAcc, gps3003c04v1TimTosOffset, 
				gps3003c04v1SurveyTout, gps3003c04v1HoldoverTime, gps3003c04v1PowerStat, gps3003c04v1PowerStatTrapEnable, gps3003c04v1AntennaStat, 
				gps3003c04v1AntennaStatTrapEnable, gps3003c04v1EthLink, gps3003c04v1EthLinkTrapEnable, gps3003c04v1AdjustingFreq, gps3003c04v1OcxoWarInProg, 
				gps3003c04v1OnePpsStat, gps3003c04v1OnePpsStatTrapEnable, gps3003c04v1OnePps, gps3003c04v1GnssDelay, gps3003c04v1PtpDelay, 
				gps3003c04v1SerialNo, gps3003c04v1GnssModVer, gps3003c04v1IpNtpSrv0, gps3003c04v1IpNtpSrv1, gps3003c04v1IpNtpSrv2, 
				gps3003c04v1IpNtpSrv3, gps3003c04v1TimeDateOk }
			STATUS current
			DESCRIPTION
				"Module GPS3003C04V1 Group"
			::= { varGroups 587701 }

		-- 1.3.6.1.4.1.10106.2.3.1.592801
		ase2008c01v1ModuleGroup OBJECT-GROUP
			OBJECTS {ase2008c01v1Index, ase2008c01v1AdcFs, ase2008c01v1Invert, ase2008c01v1BitsPerSamp, ase2008c01v1TsId, 
				ase2008c01v1PrgNum, ase2008c01v1PmtPid, ase2008c01v1BasePid, ase2008c01v1AudChEn1, ase2008c01v1AudChEn1TrapEnable, 
				ase2008c01v1AudChEn2, ase2008c01v1AudChEn2TrapEnable, ase2008c01v1AudChEn3, ase2008c01v1AudChEn3TrapEnable, ase2008c01v1AudChEn4, 
				ase2008c01v1AudChEn4TrapEnable, ase2008c01v1AudChEn5, ase2008c01v1AudChEn5TrapEnable, ase2008c01v1AudChEn6, ase2008c01v1AudChEn6TrapEnable, 
				ase2008c01v1AudChEn7, ase2008c01v1AudChEn7TrapEnable, ase2008c01v1AudChEn8, ase2008c01v1AudChEn8TrapEnable, ase2008c01v1CoarseGain, 
				ase2008c01v1AudClip, ase2008c01v1AudClipTrapEnable, ase2008c01v1SerialNo }
			STATUS current
			DESCRIPTION
				"Module ASE2008C01V1 Group"
			::= { varGroups 592801 }

		-- 1.3.6.1.4.1.10106.2.3.1.592901
		aip2000c01v1ModuleGroup OBJECT-GROUP
			OBJECTS {aip2000c01v1Index, aip2000c01v1EthMode1, aip2000c01v1Autosync, aip2000c01v1MasterSync, aip2000c01v1SpeedForce1, 
				aip2000c01v1EthMode2, aip2000c01v1SpeedForce2, aip2000c01v1EnableSdiIn, aip2000c01v1FormatTx, aip2000c01v1InterfaceSel, 
				aip2000c01v1SyncInterface, aip2000c01v1TxSrPort, aip2000c01v1TtlTx, aip2000c01v1InsGr1, aip2000c01v1InsGr2, 
				aip2000c01v1InsGr3, aip2000c01v1InsGr4, aip2000c01v1InsercionMpx, aip2000c01v1EnaAud20Bit, aip2000c01v1SwitchMode, 
				aip2000c01v1SourceSel0, aip2000c01v1SourceSel1, aip2000c01v1Mode192k, aip2000c01v1AsrcBypass0, aip2000c01v1AsrcBypass1, 
				aip2000c01v1Aes67Enable, aip2000c01v1LocalIp1Add3, aip2000c01v1LocalIp1Add2, aip2000c01v1LocalIp1Add1, aip2000c01v1LocalIp1Add0, 
				aip2000c01v1LocalIp1Msk3, aip2000c01v1LocalIp1Msk2, aip2000c01v1LocalIp1Msk1, aip2000c01v1LocalIp1Msk0, aip2000c01v1Vlan1Enable, 
				aip2000c01v1Vlan1Id, aip2000c01v1LocalIp2Add3, aip2000c01v1LocalIp2Add2, aip2000c01v1LocalIp2Add1, aip2000c01v1LocalIp2Add0, 
				aip2000c01v1LocalIp2Msk3, aip2000c01v1LocalIp2Msk2, aip2000c01v1LocalIp2Msk1, aip2000c01v1LocalIp2Msk0, aip2000c01v1Vlan2Enable, 
				aip2000c01v1Vlan2Id, aip2000c01v1LocalIpGway3, aip2000c01v1LocalIpGway2, aip2000c01v1LocalIpGway1, aip2000c01v1LocalIpGway0, 
				aip2000c01v1Profile, aip2000c01v1DomainNumber, aip2000c01v1LogAnnounceInt, aip2000c01v1LogSyncInt, aip2000c01v1LogMinDRInt, 
				aip2000c01v1StreamOk1, aip2000c01v1StreamOk1TrapEnable, aip2000c01v1BufferUnderf1, aip2000c01v1BufferUnderf1TrapEnable, aip2000c01v1BufferOverf1, 
				aip2000c01v1BufferOverf1TrapEnable, aip2000c01v1MalformedPck1, aip2000c01v1MalformedPck1TrapEnable, aip2000c01v1Rx1PckRate, aip2000c01v1Rx1LostIpPk, 
				aip2000c01v1Rx1DupIpPck, aip2000c01v1MaxBuffLevel1, aip2000c01v1MinBuffLevel1, aip2000c01v1StreamOk2, aip2000c01v1StreamOk2TrapEnable, 
				aip2000c01v1BufferUnderf2, aip2000c01v1BufferUnderf2TrapEnable, aip2000c01v1BufferOverf2, aip2000c01v1BufferOverf2TrapEnable, aip2000c01v1MalformedPck2, 
				aip2000c01v1MalformedPck2TrapEnable, aip2000c01v1Rx2PckRate, aip2000c01v1Rx2LostIpPk, aip2000c01v1Rx2DupIpPck, aip2000c01v1MaxBuffLevel2, 
				aip2000c01v1MinBuffLevel2, aip2000c01v1StreamOk3, aip2000c01v1StreamOk3TrapEnable, aip2000c01v1BufferUnderf3, aip2000c01v1BufferUnderf3TrapEnable, 
				aip2000c01v1BufferOverf3, aip2000c01v1BufferOverf3TrapEnable, aip2000c01v1MalformedPck3, aip2000c01v1MalformedPck3TrapEnable, aip2000c01v1Rx3PckRate, 
				aip2000c01v1Rx3LostIpPk, aip2000c01v1Rx3DupIpPck, aip2000c01v1MaxBuffLevel3, aip2000c01v1MinBuffLevel3, aip2000c01v1StreamOk4, 
				aip2000c01v1StreamOk4TrapEnable, aip2000c01v1BufferUnderf4, aip2000c01v1BufferUnderf4TrapEnable, aip2000c01v1BufferOverf4, aip2000c01v1BufferOverf4TrapEnable, 
				aip2000c01v1MalformedPck4, aip2000c01v1MalformedPck4TrapEnable, aip2000c01v1Rx4PckRate, aip2000c01v1Rx4LostIpPk, aip2000c01v1Rx4DupIpPck, 
				aip2000c01v1MaxBuffLevel4, aip2000c01v1MinBuffLevel4, aip2000c01v1PtpMultAdd3, aip2000c01v1PtpMultAdd2, aip2000c01v1PtpMultAdd1, 
				aip2000c01v1PtpMultAdd0, aip2000c01v1ShufOk, aip2000c01v1ShufOkTrapEnable, aip2000c01v1PtpIntSelected, aip2000c01v1Link1, 
				aip2000c01v1Link1TrapEnable, aip2000c01v1System1, aip2000c01v1System1TrapEnable, aip2000c01v1Link2, aip2000c01v1Link2TrapEnable, 
				aip2000c01v1System2, aip2000c01v1System2TrapEnable, aip2000c01v1NoSignal, aip2000c01v1NoSignalTrapEnable, aip2000c01v1Unlock, 
				aip2000c01v1UnlockTrapEnable, aip2000c01v1EdhError, aip2000c01v1Format, aip2000c01v1FormatTrapEnable, aip2000c01v1PtpState, 
				aip2000c01v1PtpStateTrapEnable, aip2000c01v1TxWorkinStat1, aip2000c01v1TxWorkinStat1TrapEnable, aip2000c01v1ArpValid1, aip2000c01v1ArpValid1TrapEnable, 
				aip2000c01v1IcmpError1, aip2000c01v1IcmpError1TrapEnable, aip2000c01v1TxWorkinStat2, aip2000c01v1TxWorkinStat2TrapEnable, aip2000c01v1ArpValid2, 
				aip2000c01v1ArpValid2TrapEnable, aip2000c01v1IcmpError2, aip2000c01v1IcmpError2TrapEnable, aip2000c01v1TxWorkinStat3, aip2000c01v1TxWorkinStat3TrapEnable, 
				aip2000c01v1ArpValid3, aip2000c01v1ArpValid3TrapEnable, aip2000c01v1IcmpError3, aip2000c01v1IcmpError3TrapEnable, aip2000c01v1TxWorkinStat4, 
				aip2000c01v1TxWorkinStat4TrapEnable, aip2000c01v1ArpValid4, aip2000c01v1ArpValid4TrapEnable, aip2000c01v1IcmpError4, aip2000c01v1IcmpError4TrapEnable, 
				aip2000c01v1AsrcUnlocked1, aip2000c01v1AsrcUnlocked1TrapEnable, aip2000c01v1ProcessorStat1, aip2000c01v1ProcessorStat1TrapEnable, aip2000c01v1AsrcUnlocked2, 
				aip2000c01v1AsrcUnlocked2TrapEnable, aip2000c01v1ProcessorStat2, aip2000c01v1ProcessorStat2TrapEnable, aip2000c01v1Seamless0, aip2000c01v1Seamless0TrapEnable, 
				aip2000c01v1Seamless1, aip2000c01v1Seamless1TrapEnable, aip2000c01v1ClkStatus, aip2000c01v1ClkStatusTrapEnable, aip2000c01v1Grp1Pres, 
				aip2000c01v1Grp1PresTrapEnable, aip2000c01v1PresenciaMpx, aip2000c01v1PresenciaMpxTrapEnable, aip2000c01v1Grp2Pres, aip2000c01v1Grp2PresTrapEnable, 
				aip2000c01v1Grp3Pres, aip2000c01v1Grp3PresTrapEnable, aip2000c01v1Grp4Pres, aip2000c01v1Grp4PresTrapEnable, aip2000c01v1SerialNo, 
				aip2000c01v1Priority0, aip2000c01v1Priority1, aip2000c01v1RecTime, aip2000c01v1PtpDelayAsym, aip2000c01v1StatReset, 
				aip2000c01v1StatMode, aip2000c01v1ClockOffset, aip2000c01v1ClockDelay, aip2000c01v1Address12En, aip2000c01v1Address22En, 
				aip2000c01v1LocalIp3Add3, aip2000c01v1LocalIp3Add2, aip2000c01v1LocalIp3Add1, aip2000c01v1LocalIp3Add0, aip2000c01v1LocalIp3Msk3, 
				aip2000c01v1LocalIp3Msk2, aip2000c01v1LocalIp3Msk1, aip2000c01v1LocalIp3Msk0, aip2000c01v1Vlan3Enable, aip2000c01v1Vlan3Id, 
				aip2000c01v1LocalIp4Add3, aip2000c01v1LocalIp4Add2, aip2000c01v1LocalIp4Add1, aip2000c01v1LocalIp4Add0, aip2000c01v1LocalIp4Msk3, 
				aip2000c01v1LocalIp4Msk2, aip2000c01v1LocalIp4Msk1, aip2000c01v1LocalIp4Msk0, aip2000c01v1Vlan4Enable, aip2000c01v1Vlan4Id, 
				aip2000c01v1RxFail1, aip2000c01v1RxFail2, aip2000c01v1RxFail3, aip2000c01v1RxFail4, aip2000c01v1VlanPriority1, 
				aip2000c01v1VlanPriority2, aip2000c01v1VlanPriority3, aip2000c01v1VlanPriority4, aip2000c01v1RxTimeRst }
			STATUS current
			DESCRIPTION
				"Module AIP2000C01V1 Group"
			::= { varGroups 592901 }

		-- 1.3.6.1.4.1.10106.2.3.1.593001
		asd2008c01v1ModuleGroup OBJECT-GROUP
			OBJECTS {asd2008c01v1Index, asd2008c01v1Invert, asd2008c01v1CoarseGain, asd2008c01v1SampFreq, asd2008c01v1SampFreqTrapEnable, 
				asd2008c01v1BitsPerSamp, asd2008c01v1BitsPerSampTrapEnable, asd2008c01v1AudClip, asd2008c01v1AudClipTrapEnable, asd2008c01v1TsLock, 
				asd2008c01v1TsLockTrapEnable, asd2008c01v1PhaseLock, asd2008c01v1PhaseLockTrapEnable, asd2008c01v1ChPres1, asd2008c01v1ChPres1TrapEnable, 
				asd2008c01v1ChPres2, asd2008c01v1ChPres2TrapEnable, asd2008c01v1ChPres3, asd2008c01v1ChPres3TrapEnable, asd2008c01v1ChPres4, 
				asd2008c01v1ChPres4TrapEnable, asd2008c01v1ChPres5, asd2008c01v1ChPres5TrapEnable, asd2008c01v1ChPres6, asd2008c01v1ChPres6TrapEnable, 
				asd2008c01v1ChPres7, asd2008c01v1ChPres7TrapEnable, asd2008c01v1ChPres8, asd2008c01v1ChPres8TrapEnable, asd2008c01v1SerialNo }
			STATUS current
			DESCRIPTION
				"Module ASD2008C01V1 Group"
			::= { varGroups 593001 }

		-- 1.3.6.1.4.1.10106.2.3.1.599301
		ded2008c01v1ModuleGroup OBJECT-GROUP
			OBJECTS {ded2008c01v1Index, ded2008c01v1AesIoMode, ded2008c01v1ChSel, ded2008c01v1SdiInDis, ded2008c01v1In1Mode, 
				ded2008c01v1In2Mode, ded2008c01v1In3Mode, ded2008c01v1In4Mode, ded2008c01v1In5Mode, ded2008c01v1In6Mode, 
				ded2008c01v1In7Mode, ded2008c01v1In8Mode, ded2008c01v1Out1AsrcEn, ded2008c01v1Out2AsrcEn, ded2008c01v1Out3AsrcEn, 
				ded2008c01v1Out4AsrcEn, ded2008c01v1In1En, ded2008c01v1In2En, ded2008c01v1In3En, ded2008c01v1In4En, 
				ded2008c01v1In5En, ded2008c01v1In6En, ded2008c01v1In7En, ded2008c01v1In8En, ded2008c01v1Out1En, 
				ded2008c01v1Out2En, ded2008c01v1Out3En, ded2008c01v1Out4En, ded2008c01v1Out5En, ded2008c01v1Out6En, 
				ded2008c01v1Out7En, ded2008c01v1Out8En, ded2008c01v1SdiFmt, ded2008c01v1SdiInFail, ded2008c01v1SdiInFailTrapEnable, 
				ded2008c01v1SdiG1Fail, ded2008c01v1SdiG1FailTrapEnable, ded2008c01v1SdiG2Fail, ded2008c01v1SdiG2FailTrapEnable, ded2008c01v1SdiG3Fail, 
				ded2008c01v1SdiG3FailTrapEnable, ded2008c01v1SdiG4Fail, ded2008c01v1SdiG4FailTrapEnable, ded2008c01v1Ref27mFail, ded2008c01v1Ref27mFailTrapEnable, 
				ded2008c01v1AudioProcFail, ded2008c01v1AudioProcFailTrapEnable, ded2008c01v1In1AudFail, ded2008c01v1In1AudFailTrapEnable, ded2008c01v1In1RefFail, 
				ded2008c01v1In1RefFailTrapEnable, ded2008c01v1In2AudFail, ded2008c01v1In2AudFailTrapEnable, ded2008c01v1In2RefFail, ded2008c01v1In2RefFailTrapEnable, 
				ded2008c01v1In3AudFail, ded2008c01v1In3AudFailTrapEnable, ded2008c01v1In3RefFail, ded2008c01v1In3RefFailTrapEnable, ded2008c01v1In4AudFail, 
				ded2008c01v1In4AudFailTrapEnable, ded2008c01v1In4RefFail, ded2008c01v1In4RefFailTrapEnable, ded2008c01v1In5AudFail, ded2008c01v1In5AudFailTrapEnable, 
				ded2008c01v1In6AudFail, ded2008c01v1In6AudFailTrapEnable, ded2008c01v1In7AudFail, ded2008c01v1In7AudFailTrapEnable, ded2008c01v1In8AudFail, 
				ded2008c01v1In8AudFailTrapEnable, ded2008c01v1In1FreqFail, ded2008c01v1In2FreqFail, ded2008c01v1In3FreqFail, ded2008c01v1In4FreqFail, 
				ded2008c01v1In5FreqFail, ded2008c01v1In6FreqFail, ded2008c01v1In7FreqFail, ded2008c01v1In8FreqFail, ded2008c01v1SdiInFmt, 
				ded2008c01v1SerialNo }
			STATUS current
			DESCRIPTION
				"Module DED2008C01V1 Group"
			::= { varGroups 599301 }

		-- 1.3.6.1.4.1.10106.2.3.1.600801
		uvd2000c01v1ModuleGroup OBJECT-GROUP
			OBJECTS {uvd2000c01v1Index, uvd2000c01v1Input, uvd2000c01v1InputTrapEnable, uvd2000c01v1BckTxEn, uvd2000c01v1Los, 
				uvd2000c01v1LosTrapEnable, uvd2000c01v1Unlock, uvd2000c01v1UnlockTrapEnable, uvd2000c01v1Rate, uvd2000c01v1RateTrapEnable, 
				uvd2000c01v1SerialNo }
			STATUS current
			DESCRIPTION
				"Module UVD2000C01V1 Group"
			::= { varGroups 600801 }

		-- 1.3.6.1.4.1.10106.2.3.1.607801
		deb2008c01v1ModuleGroup OBJECT-GROUP
			OBJECTS {deb2008c01v1Index, deb2008c01v1ActivePreset, deb2008c01v1LoadPreset, deb2008c01v1SavePreset, deb2008c01v1ManNAuto, 
				deb2008c01v1AesInNOut, deb2008c01v1BaseSlot, deb2008c01v1SlotUsedOne, deb2008c01v1SlotUsedTwo, deb2008c01v1OvldLevel, 
				deb2008c01v1ChSel, deb2008c01v1In1Mode, deb2008c01v1In2Mode, deb2008c01v1In3Mode, deb2008c01v1In4Mode, 
				deb2008c01v1In5Mode, deb2008c01v1In6Mode, deb2008c01v1In7Mode, deb2008c01v1In8Mode, deb2008c01v1Out1AsrcEn, 
				deb2008c01v1Out2AsrcEn, deb2008c01v1Out3AsrcEn, deb2008c01v1Out4AsrcEn, deb2008c01v1Gain0, deb2008c01v1Phase0, 
				deb2008c01v1Gain1, deb2008c01v1Phase1, deb2008c01v1Gain2, deb2008c01v1Phase2, deb2008c01v1Gain3, 
				deb2008c01v1Phase3, deb2008c01v1Gain4, deb2008c01v1Phase4, deb2008c01v1Gain5, deb2008c01v1Phase5, 
				deb2008c01v1Gain6, deb2008c01v1Phase6, deb2008c01v1Gain7, deb2008c01v1Phase7, deb2008c01v1Gain8, 
				deb2008c01v1Phase8, deb2008c01v1Gain9, deb2008c01v1Phase9, deb2008c01v1Gain10, deb2008c01v1Phase10, 
				deb2008c01v1Gain11, deb2008c01v1Phase11, deb2008c01v1Gain12, deb2008c01v1Phase12, deb2008c01v1Gain13, 
				deb2008c01v1Phase13, deb2008c01v1Gain14, deb2008c01v1Phase14, deb2008c01v1Gain15, deb2008c01v1Phase15, 
				deb2008c01v1BusTimFail, deb2008c01v1BusTimUnlck, deb2008c01v1BusAudFail, deb2008c01v1BusAudError, deb2008c01v1AudClipEr, 
				deb2008c01v1AudClipErTrapEnable, deb2008c01v1AudPresFail, deb2008c01v1AudPresFailTrapEnable, deb2008c01v1AudInsFail, deb2008c01v1AudInsFailTrapEnable, 
				deb2008c01v1AudOvldEr, deb2008c01v1AudOvldErTrapEnable, deb2008c01v1Slot1Pres, deb2008c01v1Slot2Pres, deb2008c01v1Slot3Pres, 
				deb2008c01v1Slot4Pres, deb2008c01v1Slot5Pres, deb2008c01v1Slot6Pres, deb2008c01v1Slot7Pres, deb2008c01v1Slot8Pres, 
				deb2008c01v1Aes1Pres, deb2008c01v1Aes1RefPres, deb2008c01v1Aes2Pres, deb2008c01v1Aes2RefPres, deb2008c01v1Aes3Pres, 
				deb2008c01v1Aes3RefPres, deb2008c01v1Aes4Pres, deb2008c01v1Aes4RefPres, deb2008c01v1Aes5Pres, deb2008c01v1Aes6Pres, 
				deb2008c01v1Aes7Pres, deb2008c01v1Aes8Pres, deb2008c01v1Aes1AsyncFail, deb2008c01v1Aes2AsyncFail, deb2008c01v1Aes3AsyncFail, 
				deb2008c01v1Aes4AsyncFail, deb2008c01v1Aes5AsyncFail, deb2008c01v1Aes6AsyncFail, deb2008c01v1Aes7AsyncFail, deb2008c01v1Aes8AsyncFail, 
				deb2008c01v1AsrcRefFail, deb2008c01v1SerialNo }
			STATUS current
			DESCRIPTION
				"Module DEB2008C01V1 Group"
			::= { varGroups 607801 }

		-- 1.3.6.1.4.1.10106.2.3.1.607901
		def2008c01v1ModuleGroup OBJECT-GROUP
			OBJECTS {def2008c01v1Index, def2008c01v1ActivePreset, def2008c01v1LoadPreset, def2008c01v1SavePreset, def2008c01v1AesIoMode, 
				def2008c01v1AudioFailMode, def2008c01v1Out1AsrcEn, def2008c01v1Out2AsrcEn, def2008c01v1Out3AsrcEn, def2008c01v1Out4AsrcEn, 
				def2008c01v1In1Mode, def2008c01v1In2Mode, def2008c01v1In3Mode, def2008c01v1In4Mode, def2008c01v1In5Mode, 
				def2008c01v1In6Mode, def2008c01v1In7Mode, def2008c01v1In8Mode, def2008c01v1AesIn1Pres, def2008c01v1AesIn1PresTrapEnable, 
				def2008c01v1Aes1RefPres, def2008c01v1Aes1RefPresTrapEnable, def2008c01v1AesIn2Pres, def2008c01v1AesIn2PresTrapEnable, def2008c01v1Aes2RefPres, 
				def2008c01v1Aes2RefPresTrapEnable, def2008c01v1AesIn3Pres, def2008c01v1AesIn3PresTrapEnable, def2008c01v1Aes3RefPres, def2008c01v1Aes3RefPresTrapEnable, 
				def2008c01v1AesIn4Pres, def2008c01v1AesIn4PresTrapEnable, def2008c01v1Aes4RefPres, def2008c01v1Aes4RefPresTrapEnable, def2008c01v1AesIn5Pres, 
				def2008c01v1AesIn5PresTrapEnable, def2008c01v1AesIn6Pres, def2008c01v1AesIn6PresTrapEnable, def2008c01v1AesIn7Pres, def2008c01v1AesIn7PresTrapEnable, 
				def2008c01v1AesIn8Pres, def2008c01v1AesIn8PresTrapEnable, def2008c01v1AesIn1Locked, def2008c01v1AesIn2Locked, def2008c01v1AesIn3Locked, 
				def2008c01v1AesIn4Locked, def2008c01v1AesIn5Locked, def2008c01v1AesIn6Locked, def2008c01v1AesIn7Locked, def2008c01v1AesIn8Locked, 
				def2008c01v1BackplaneLocked, def2008c01v1BackplaneLockedTrapEnable, def2008c01v1L2rIn1Pres, def2008c01v1L2rIn2Pres, def2008c01v1L2rIn3Pres, 
				def2008c01v1L2rIn4Pres, def2008c01v1L2rIn5Pres, def2008c01v1L2rIn6Pres, def2008c01v1L2rIn7Pres, def2008c01v1L2rIn8Pres, 
				def2008c01v1L2rIn9Pres, def2008c01v1L2rIn10Pres, def2008c01v1L2rIn11Pres, def2008c01v1L2rIn12Pres, def2008c01v1L2rIn13Pres, 
				def2008c01v1L2rIn14Pres, def2008c01v1L2rIn15Pres, def2008c01v1L2rIn16Pres, def2008c01v1R2lIn1Pres, def2008c01v1R2lIn2Pres, 
				def2008c01v1R2lIn3Pres, def2008c01v1R2lIn4Pres, def2008c01v1R2lIn5Pres, def2008c01v1R2lIn6Pres, def2008c01v1R2lIn7Pres, 
				def2008c01v1R2lIn8Pres, def2008c01v1R2lIn9Pres, def2008c01v1R2lIn10Pres, def2008c01v1R2lIn11Pres, def2008c01v1R2lIn12Pres, 
				def2008c01v1R2lIn13Pres, def2008c01v1R2lIn14Pres, def2008c01v1R2lIn15Pres, def2008c01v1R2lIn16Pres, def2008c01v1SerialNo }
			STATUS current
			DESCRIPTION
				"Module DEF2008C01V1 Group"
			::= { varGroups 607901 }

		-- 1.3.6.1.4.1.10106.2.3.1.609201
		dad2000c01v1ModuleGroup OBJECT-GROUP
			OBJECTS {dad2000c01v1Index, dad2000c01v1SigFail, dad2000c01v1SigFailTrapEnable, dad2000c01v1SigLow, dad2000c01v1SigLowTrapEnable, 
				dad2000c01v1SignalLevel }
			STATUS current
			DESCRIPTION
				"Module DAD2000C01V1 Group"
			::= { varGroups 609201 }

		-- 1.3.6.1.4.1.10106.2.3.1.612801
		vtr2000c01v1ModuleGroup OBJECT-GROUP
			OBJECTS {vtr2000c01v1Index, vtr2000c01v1ActivePreset, vtr2000c01v1LoadPreset, vtr2000c01v1SavePreset, vtr2000c01v1TcSrc1, 
				vtr2000c01v1TcSrc2, vtr2000c01v1EnLtcIn, vtr2000c01v1TcToTs, vtr2000c01v1LtcEmbSrc1, vtr2000c01v1LtcEmbSrc2, 
				vtr2000c01v1MeasType, vtr2000c01v1MeasLdOff, vtr2000c01v1MeasOffSign, vtr2000c01v1IpAdd0, vtr2000c01v1IpAdd1, 
				vtr2000c01v1IpAdd2, vtr2000c01v1IpAdd3, vtr2000c01v1IpMask0, vtr2000c01v1IpMask1, vtr2000c01v1IpMask2, 
				vtr2000c01v1IpMask3, vtr2000c01v1IpGway0, vtr2000c01v1IpGway1, vtr2000c01v1IpGway2, vtr2000c01v1IpGway3, 
				vtr2000c01v1NtpIpAddress0, vtr2000c01v1NtpIpAddress1, vtr2000c01v1NtpIpAddress2, vtr2000c01v1NtpIpAddress3, vtr2000c01v1Measure, 
				vtr2000c01v1Format1, vtr2000c01v1SdiInvalid1, vtr2000c01v1NoSignal1, vtr2000c01v1CrcErr1, vtr2000c01v1TcSrcFail1, 
				vtr2000c01v1AtcVitcPres1, vtr2000c01v1AtcLtcPres1, vtr2000c01v1DvitcPres1, vtr2000c01v1LtcEmbPres1, vtr2000c01v1AudGrpPres11, 
				vtr2000c01v1AudGrpPres12, vtr2000c01v1AudGrpPres13, vtr2000c01v1AudGrpPres14, vtr2000c01v1Format2, vtr2000c01v1SdiInvalid2, 
				vtr2000c01v1NoSignal2, vtr2000c01v1CrcErr2, vtr2000c01v1TcSrcFail2, vtr2000c01v1AtcVitcPres2, vtr2000c01v1AtcLtcPres2, 
				vtr2000c01v1DvitcPres2, vtr2000c01v1LtcEmbPres2, vtr2000c01v1AudGrpPres21, vtr2000c01v1AudGrpPres22, vtr2000c01v1AudGrpPres23, 
				vtr2000c01v1AudGrpPres24, vtr2000c01v1LtcInFail, vtr2000c01v1BusRefFail, vtr2000c01v1LockSrc, vtr2000c01v1MeasRdy, 
				vtr2000c01v1EthLink, vtr2000c01v1EthSystem, vtr2000c01v1SerialNo }
			STATUS current
			DESCRIPTION
				"Module VTR2000C01V1 Group"
			::= { varGroups 612801 }

		-- 1.3.6.1.4.1.10106.2.3.1.616301
		gpd2000c01v1ModuleGroup OBJECT-GROUP
			OBJECTS {gpd2000c01v1Index, gpd2000c01v1VccGnssLow, gpd2000c01v1IccAntennaLow, gpd2000c01v1IccAntennaHigh, gpd2000c01v1VccGnss1Fail, 
				gpd2000c01v1VccGnss1FailTrapEnable, gpd2000c01v1VccGnss2Fail, gpd2000c01v1VccGnss2FailTrapEnable, gpd2000c01v1VccGnss3Fail, gpd2000c01v1VccGnss3FailTrapEnable, 
				gpd2000c01v1VccGnss4Fail, gpd2000c01v1VccGnss4FailTrapEnable, gpd2000c01v1VccAntennaFail, gpd2000c01v1VccAntennaFailTrapEnable, gpd2000c01v1IccAntennaFail, 
				gpd2000c01v1IccAntennaFailTrapEnable, gpd2000c01v1NoAntenna, gpd2000c01v1NoAntennaTrapEnable, gpd2000c01v1DcGnss1, gpd2000c01v1DcGnss2, 
				gpd2000c01v1DcGnss3, gpd2000c01v1DcGnss4, gpd2000c01v1AntennaVcc, gpd2000c01v1AntennaIcc, gpd2000c01v1SerialNo }
			STATUS current
			DESCRIPTION
				"Module GPD2000C01V1 Group"
			::= { varGroups 616301 }

		-- 1.3.6.1.4.1.10106.2.3.1.620401
		hxc2000c02v1ModuleGroup OBJECT-GROUP
			OBJECTS {hxc2000c02v1Index, hxc2000c02v1ActivePreset, hxc2000c02v1LoadPreset, hxc2000c02v1SavePreset, hxc2000c02v1AnaRefFmt, 
				hxc2000c02v1AnaRefFmtTrapEnable, hxc2000c02v1GenlockMode, hxc2000c02v1EnaAud20Bit, hxc2000c02v1FailMode, hxc2000c02v1ModeConv, 
				hxc2000c02v1ModeConvTrapEnable, hxc2000c02v1OutAfd, hxc2000c02v1OutAfdTrapEnable, hxc2000c02v1OutCf, hxc2000c02v1OutCfTrapEnable, 
				hxc2000c02v1Esc11, hxc2000c02v1InAfdExpct, hxc2000c02v1InAfdExpctTrapEnable, hxc2000c02v1InCfExpct, hxc2000c02v1InCfExpctTrapEnable, 
				hxc2000c02v1TxFmt, hxc2000c02v1TxFmtTrapEnable, hxc2000c02v1DeintAlgorithm, hxc2000c02v1DeintAlgorithmTrapEnable, hxc2000c02v1OutEnaS2016, 
				hxc2000c02v1OutEnaVii, hxc2000c02v1OutEnaWss, hxc2000c02v1OutEnaVitc, hxc2000c02v1OutEnaAtc, hxc2000c02v1OutEnaTxt, 
				hxc2000c02v1OutEnaCea608, hxc2000c02v1VDelay, hxc2000c02v1HDelay, hxc2000c02v1Grp1P0Gain, hxc2000c02v1Grp1P0Phase, 
				hxc2000c02v1Grp1P1Gain, hxc2000c02v1Grp1P1Phase, hxc2000c02v1Grp2P0Gain, hxc2000c02v1Grp2P0Phase, hxc2000c02v1Grp2P1Gain, 
				hxc2000c02v1Grp2P1Phase, hxc2000c02v1Grp3P0Gain, hxc2000c02v1Grp3P0Phase, hxc2000c02v1Grp3P1Gain, hxc2000c02v1Grp3P1Phase, 
				hxc2000c02v1Grp4P0Gain, hxc2000c02v1Grp4P0Phase, hxc2000c02v1Grp4P1Gain, hxc2000c02v1Grp4P1Phase, hxc2000c02v1MuteEna, 
				hxc2000c02v1StatFlash, hxc2000c02v1InPhyFail, hxc2000c02v1InPhyFailTrapEnable, hxc2000c02v1InFmtFail, hxc2000c02v1InFmtFailTrapEnable, 
				hxc2000c02v1InIncFail, hxc2000c02v1InIncFailTrapEnable, hxc2000c02v1InPresCrcFail, hxc2000c02v1InCrcFail, hxc2000c02v1InCrcFailTrapEnable, 
				hxc2000c02v1InPrsS352Fail, hxc2000c02v1InS352Fail, hxc2000c02v1PresS2016Fail, hxc2000c02v1ErrS2016Fail, hxc2000c02v1PresAudG1Fail, 
				hxc2000c02v1PresAudG1FailTrapEnable, hxc2000c02v1PresAudG2Fail, hxc2000c02v1PresAudG2FailTrapEnable, hxc2000c02v1PresAudG3Fail, hxc2000c02v1PresAudG3FailTrapEnable, 
				hxc2000c02v1PresAudG4Fail, hxc2000c02v1PresAudG4FailTrapEnable, hxc2000c02v1RefFail, hxc2000c02v1RefFailTrapEnable, hxc2000c02v1RefFmtFail, 
				hxc2000c02v1RefFmtFailTrapEnable, hxc2000c02v1LockFail, hxc2000c02v1LockFailTrapEnable, hxc2000c02v1UxcPres, hxc2000c02v1UxcPresTrapEnable, 
				hxc2000c02v1AudPair0Fail, hxc2000c02v1AudPair0FailTrapEnable, hxc2000c02v1AudPair1Fail, hxc2000c02v1AudPair1FailTrapEnable, hxc2000c02v1AudPair2Fail, 
				hxc2000c02v1AudPair2FailTrapEnable, hxc2000c02v1AudPair3Fail, hxc2000c02v1AudPair3FailTrapEnable, hxc2000c02v1AudPair4Fail, hxc2000c02v1AudPair4FailTrapEnable, 
				hxc2000c02v1AudPair5Fail, hxc2000c02v1AudPair5FailTrapEnable, hxc2000c02v1AudPair6Fail, hxc2000c02v1AudPair6FailTrapEnable, hxc2000c02v1AudPair7Fail, 
				hxc2000c02v1AudPair7FailTrapEnable, hxc2000c02v1InAfdDetct, hxc2000c02v1InAfdDetctTrapEnable, hxc2000c02v1InCfDetct, hxc2000c02v1InCfDetctTrapEnable, 
				hxc2000c02v1InFormat, hxc2000c02v1InFormatTrapEnable, hxc2000c02v1RefFormat, hxc2000c02v1RefFormatTrapEnable, hxc2000c02v1TxFormat, 
				hxc2000c02v1TxFormatTrapEnable, hxc2000c02v1TxtPres, hxc2000c02v1VitcPres, hxc2000c02v1Mute, hxc2000c02v1Black, 
				hxc2000c02v1Gpi1, hxc2000c02v1Gpi2, hxc2000c02v1Gpi3, hxc2000c02v1Gpi4, hxc2000c02v1SerialNo }
			STATUS current
			DESCRIPTION
				"Module HXC2000C02V1 Group"
			::= { varGroups 620401 }

		-- 1.3.6.1.4.1.10106.2.3.1.623301
		mpx2000c01v1ModuleGroup OBJECT-GROUP
			OBJECTS {mpx2000c01v1Index, mpx2000c01v1AudioMpxN, mpx2000c01v1AudioMpxNTrapEnable, mpx2000c01v1Control, mpx2000c01v1ControlTrapEnable, 
				mpx2000c01v1Preemph, mpx2000c01v1AudInLevAdj, mpx2000c01v1NoSigThr, mpx2000c01v1NoSigTout, mpx2000c01v1MpxFail, 
				mpx2000c01v1MpxFailTrapEnable, mpx2000c01v1AudFail, mpx2000c01v1AudFailTrapEnable, mpx2000c01v1Gpi, mpx2000c01v1GpiTrapEnable, 
				mpx2000c01v1Gpo, mpx2000c01v1MpxPeakV, mpx2000c01v1InsPeakV, mpx2000c01v1MpxPeakDbfs, mpx2000c01v1AudPeakDbfs, 
				mpx2000c01v1SerialNo }
			STATUS current
			DESCRIPTION
				"Module MPX2000C01V1 Group"
			::= { varGroups 623301 }

		-- 1.3.6.1.4.1.10106.2.3.1.627101
		rfa2018c01v1ModuleGroup OBJECT-GROUP
			OBJECTS {rfa2018c01v1Index, rfa2018c01v1VoltFailMask, rfa2018c01v1CurrFailMask, rfa2018c01v1TempFailMask, rfa2018c01v1MinVoltThr, 
				rfa2018c01v1MaxVoltThr, rfa2018c01v1MinCurrThr, rfa2018c01v1MaxCurrThr, rfa2018c01v1MaxTempThr, rfa2018c01v1VoltFail, 
				rfa2018c01v1VoltFailTrapEnable, rfa2018c01v1CurrFail, rfa2018c01v1CurrFailTrapEnable, rfa2018c01v1TempFail, rfa2018c01v1TempFailTrapEnable, 
				rfa2018c01v1ActVolt, rfa2018c01v1ActCurr, rfa2018c01v1ActTemp, rfa2018c01v1SerialNo }
			STATUS current
			DESCRIPTION
				"Module RFA2018C01V1 Group"
			::= { varGroups 627101 }
		

		-- 1.3.6.1.4.1.10106.2.3.2
		trapGroup OBJECT IDENTIFIER ::= { albalaConformance 2 }

		
		-- 1.3.6.1.4.1.10106.2.3.2.1
		genTrapGroup NOTIFICATION-GROUP
			NOTIFICATIONS { moduleStatusChange, agentStatusChange }
			STATUS current
			DESCRIPTION 
				"Description."
			::= { trapGroup 1 }

		

		-- 1.3.6.1.4.1.10106.2.3.2.125101
		vct3000p01v1TrapGroup NOTIFICATION-GROUP
		NOTIFICATIONS {vct3000p01v1ModeTrap, vct3000p01v1InputTrap, vct3000p01v1MainFailTrap, vct3000p01v1ResFailTrap }
			STATUS current
			DESCRIPTION
				"Module VCT3000P01V1 Trap Group"
			::= { trapGroup 125101 }

		-- 1.3.6.1.4.1.10106.2.3.2.126001
		vct3000c02v1TrapGroup NOTIFICATION-GROUP
		NOTIFICATIONS {vct3000c02v1ModeTrap, vct3000c02v1InputTrap, vct3000c02v1MainFailTrap, vct3000c02v1ResFailTrap }
			STATUS current
			DESCRIPTION
				"Module VCT3000C02V1 Trap Group"
			::= { trapGroup 126001 }

		-- 1.3.6.1.4.1.10106.2.3.2.126201
		vct3000c04v1TrapGroup NOTIFICATION-GROUP
		NOTIFICATIONS {vct3000c04v1ModeTrap, vct3000c04v1InputTrap, vct3000c04v1MainFailTrap, vct3000c04v1ResFailTrap }
			STATUS current
			DESCRIPTION
				"Module VCT3000C04V1 Trap Group"
			::= { trapGroup 126201 }

		-- 1.3.6.1.4.1.10106.2.3.2.126301
		vct3000c05v1TrapGroup NOTIFICATION-GROUP
		NOTIFICATIONS {vct3000c05v1ModeTrap, vct3000c05v1InputTrap, vct3000c05v1MainFailTrap, vct3000c05v1ResFailTrap }
			STATUS current
			DESCRIPTION
				"Module VCT3000C05V1 Trap Group"
			::= { trapGroup 126301 }

		-- 1.3.6.1.4.1.10106.2.3.2.128301
		dvm3000p01v1TrapGroup NOTIFICATION-GROUP
		NOTIFICATIONS {dvm3000p01v1NoSigATrap, dvm3000p01v1NoSigBTrap }
			STATUS current
			DESCRIPTION
				"Module DVM3000P01V1 Trap Group"
			::= { trapGroup 128301 }

		-- 1.3.6.1.4.1.10106.2.3.2.129101
		dsw3000p01v1TrapGroup NOTIFICATION-GROUP
		NOTIFICATIONS {dsw3000p01v1ModeTrap, dsw3000p01v1InputTrap, dsw3000p01v1MainFailTrap, dsw3000p01v1ExtMainFailTrap, dsw3000p01v1ResFailTrap, 
				dsw3000p01v1ExtResFailTrap, dsw3000p01v1AuxFailTrap, dsw3000p01v1ExtAuxFailTrap }
			STATUS current
			DESCRIPTION
				"Module DSW3000P01V1 Trap Group"
			::= { trapGroup 129101 }

		-- 1.3.6.1.4.1.10106.2.3.2.130101
		lns3000p01v1TrapGroup NOTIFICATION-GROUP
		NOTIFICATIONS {lns3000p01v1NoSignalPgmTrap, lns3000p01v1TimingErrTrap, lns3000p01v1NoSignalRefTrap }
			STATUS current
			DESCRIPTION
				"Module LNS3000P01V1 Trap Group"
			::= { trapGroup 130101 }

		-- 1.3.6.1.4.1.10106.2.3.2.131502
		dli3000p01v2TrapGroup NOTIFICATION-GROUP
		NOTIFICATIONS {dli3000p01v2NoSigTrap }
			STATUS current
			DESCRIPTION
				"Module DLI3000P01V2 Trap Group"
			::= { trapGroup 131502 }

		-- 1.3.6.1.4.1.10106.2.3.2.133501
		tly3032p01v1TrapGroup NOTIFICATION-GROUP
		NOTIFICATIONS {tly3032p01v1Gpi1Trap, tly3032p01v1Gpi2Trap, tly3032p01v1Gpi3Trap, tly3032p01v1Gpi4Trap, tly3032p01v1Gpi5Trap, 
				tly3032p01v1Gpi6Trap, tly3032p01v1Gpi7Trap, tly3032p01v1Gpi8Trap, tly3032p01v1Gpi9Trap, tly3032p01v1Gpi10Trap, 
				tly3032p01v1Gpi11Trap, tly3032p01v1Gpi12Trap, tly3032p01v1Gpi13Trap, tly3032p01v1Gpi14Trap, tly3032p01v1Gpi15Trap, 
				tly3032p01v1Gpi16Trap, tly3032p01v1Gpi17Trap, tly3032p01v1Gpi18Trap, tly3032p01v1Gpi19Trap, tly3032p01v1Gpi20Trap, 
				tly3032p01v1Gpi21Trap, tly3032p01v1Gpi22Trap, tly3032p01v1Gpi23Trap, tly3032p01v1Gpi24Trap, tly3032p01v1Gpi25Trap, 
				tly3032p01v1Gpi26Trap, tly3032p01v1Gpi27Trap, tly3032p01v1Gpi28Trap, tly3032p01v1Gpi29Trap, tly3032p01v1Gpi30Trap, 
				tly3032p01v1Gpi31Trap, tly3032p01v1Gpi32Trap }
			STATUS current
			DESCRIPTION
				"Module TLY3032P01V1 Trap Group"
			::= { trapGroup 133501 }

		-- 1.3.6.1.4.1.10106.2.3.2.134801
		aac3000p01v1TrapGroup NOTIFICATION-GROUP
		NOTIFICATIONS {aac3000p01v1NoVidTrap, aac3000p01v1NoAesTrap, aac3000p01v1NoWclkTrap, aac3000p01v1UnlockTrap, aac3000p01v1OvldS1ChaTrap, 
				aac3000p01v1OvldS1ChbTrap, aac3000p01v1OvldS2ChaTrap, aac3000p01v1OvldS2ChbTrap }
			STATUS current
			DESCRIPTION
				"Module AAC3000P01V1 Trap Group"
			::= { trapGroup 134801 }

		-- 1.3.6.1.4.1.10106.2.3.2.134901
		aem3000p01v1TrapGroup NOTIFICATION-GROUP
		NOTIFICATIONS {aem3000p01v1GroupTrap, aem3000p01v1NoSignalTrap, aem3000p01v1SilOut1Trap, aem3000p01v1SilOut2Trap, aem3000p01v1OvlOut1Trap, 
				aem3000p01v1OvlOut2Trap }
			STATUS current
			DESCRIPTION
				"Module AEM3000P01V1 Trap Group"
			::= { trapGroup 134901 }

		-- 1.3.6.1.4.1.10106.2.3.2.135801
		ade3000p01v1TrapGroup NOTIFICATION-GROUP
		NOTIFICATIONS {ade3000p01v1GroupTrap, ade3000p01v1NoSignalTrap, ade3000p01v1NsamAes1Trap, ade3000p01v1NsamAes2Trap, ade3000p01v1SilOut1Trap, 
				ade3000p01v1SilOut2Trap, ade3000p01v1OvlOut1Trap, ade3000p01v1OvlOut2Trap }
			STATUS current
			DESCRIPTION
				"Module ADE3000P01V1 Trap Group"
			::= { trapGroup 135801 }

		-- 1.3.6.1.4.1.10106.2.3.2.136301
		dsw3000c02v1TrapGroup NOTIFICATION-GROUP
		NOTIFICATIONS {dsw3000c02v1ModeTrap, dsw3000c02v1InputTrap, dsw3000c02v1MainFailTrap, dsw3000c02v1ExtMainFailTrap, dsw3000c02v1ResFailTrap, 
				dsw3000c02v1ExtResFailTrap, dsw3000c02v1AuxFailTrap, dsw3000c02v1ExtAuxFailTrap }
			STATUS current
			DESCRIPTION
				"Module DSW3000C02V1 Trap Group"
			::= { trapGroup 136301 }

		-- 1.3.6.1.4.1.10106.2.3.2.136601
		dem3000p01v1TrapGroup NOTIFICATION-GROUP
		NOTIFICATIONS {dem3000p01v1GroupATrap, dem3000p01v1GroupBTrap, dem3000p01v1NoSignalATrap, dem3000p01v1NoAes1ATrap, dem3000p01v1UlckAes1ATrap, 
				dem3000p01v1NoAes2ATrap, dem3000p01v1UlckAes2ATrap, dem3000p01v1NoSignalBTrap, dem3000p01v1NoAes1BTrap, dem3000p01v1UlckAes1BTrap, 
				dem3000p01v1NoAes2BTrap, dem3000p01v1UlckAes2BTrap }
			STATUS current
			DESCRIPTION
				"Module DEM3000P01V1 Trap Group"
			::= { trapGroup 136601 }

		-- 1.3.6.1.4.1.10106.2.3.2.137101
		dde3000p01v1TrapGroup NOTIFICATION-GROUP
		NOTIFICATIONS {dde3000p01v1GroupATrap, dde3000p01v1GroupBTrap, dde3000p01v1NoSignalATrap, dde3000p01v1NsamAes1ATrap, dde3000p01v1NsamAes2ATrap, 
				dde3000p01v1NoSignalBTrap, dde3000p01v1NsamAes1BTrap, dde3000p01v1NsamAes2BTrap }
			STATUS current
			DESCRIPTION
				"Module DDE3000P01V1 Trap Group"
			::= { trapGroup 137101 }

		-- 1.3.6.1.4.1.10106.2.3.2.139701
		aad3034p01v1TrapGroup NOTIFICATION-GROUP
		NOTIFICATIONS {aad3034p01v1SilenceRATrap, aad3034p01v1SilenceLATrap, aad3034p01v1AntiphaseATrap, aad3034p01v1OverloadRATrap, aad3034p01v1OverloadLATrap, 
				aad3034p01v1OverloadRlATrap, aad3034p01v1SilenceRBTrap, aad3034p01v1SilenceLBTrap, aad3034p01v1AntiphaseBTrap, aad3034p01v1OverloadRBTrap, 
				aad3034p01v1OverloadLBTrap, aad3034p01v1OverloadRlBTrap }
			STATUS current
			DESCRIPTION
				"Module AAD3034P01V1 Trap Group"
			::= { trapGroup 139701 }

		-- 1.3.6.1.4.1.10106.2.3.2.141201
		frs3000p01v1TrapGroup NOTIFICATION-GROUP
		NOTIFICATIONS {frs3000p01v1NoRefTrap, frs3000p01v1RefUnlockTrap, frs3000p01v1NoSigTrap, frs3000p01v1SubcarrUnlockTrap }
			STATUS current
			DESCRIPTION
				"Module FRS3000P01V1 Trap Group"
			::= { trapGroup 141201 }

		-- 1.3.6.1.4.1.10106.2.3.2.141701
		pds3000p01v1TrapGroup NOTIFICATION-GROUP
		NOTIFICATIONS {pds3000p01v1NoRefTrap, pds3000p01v1RefUnlockTrap, pds3000p01v1NoCcvsTrap, pds3000p01v1CcvsUnlockTrap, pds3000p01v1DecOvldTrap, 
				pds3000p01v1AdOvldTrap }
			STATUS current
			DESCRIPTION
				"Module PDS3000P01V1 Trap Group"
			::= { trapGroup 141701 }

		-- 1.3.6.1.4.1.10106.2.3.2.147801
		aad3024p01v1TrapGroup NOTIFICATION-GROUP
		NOTIFICATIONS {aad3024p01v1SilenceRATrap, aad3024p01v1SilenceLATrap, aad3024p01v1AntiphaseATrap, aad3024p01v1OverloadRATrap, aad3024p01v1OverloadLATrap, 
				aad3024p01v1SilenceRBTrap, aad3024p01v1SilenceLBTrap, aad3024p01v1AntiphaseBTrap, aad3024p01v1OverloadRBTrap, aad3024p01v1OverloadLBTrap }
			STATUS current
			DESCRIPTION
				"Module AAD3024P01V1 Trap Group"
			::= { trapGroup 147801 }

		-- 1.3.6.1.4.1.10106.2.3.2.147901
		aad3014p01v1TrapGroup NOTIFICATION-GROUP
		NOTIFICATIONS {aad3014p01v1SilenceRTrap, aad3014p01v1SilenceLTrap, aad3014p01v1AntiphaseTrap, aad3014p01v1OverloadRTrap, aad3014p01v1OverloadLTrap, 
				aad3014p01v1OverloadRlTrap }
			STATUS current
			DESCRIPTION
				"Module AAD3014P01V1 Trap Group"
			::= { trapGroup 147901 }

		-- 1.3.6.1.4.1.10106.2.3.2.147902
		aad3014c01v2TrapGroup NOTIFICATION-GROUP
		NOTIFICATIONS {aad3014c01v2SilenceRTrap, aad3014c01v2SilenceLTrap, aad3014c01v2OverloadRTrap, aad3014c01v2OverloadLTrap }
			STATUS current
			DESCRIPTION
				"Module AAD3014C01V2 Trap Group"
			::= { trapGroup 147902 }

		-- 1.3.6.1.4.1.10106.2.3.2.149301
		sct3000c02v1TrapGroup NOTIFICATION-GROUP
		NOTIFICATIONS {sct3000c02v1ModeTrap, sct3000c02v1InputTrap }
			STATUS current
			DESCRIPTION
				"Module SCT3000C02V1 Trap Group"
			::= { trapGroup 149301 }

		-- 1.3.6.1.4.1.10106.2.3.2.150501
		dat3000p01v1TrapGroup NOTIFICATION-GROUP
		NOTIFICATIONS {dat3000p01v1LockAesTrap, dat3000p01v1LockVidTrap, dat3000p01v1LockWclkTrap }
			STATUS current
			DESCRIPTION
				"Module DAT3000P01V1 Trap Group"
			::= { trapGroup 150501 }

		-- 1.3.6.1.4.1.10106.2.3.2.157401
		cav3000p01v1TrapGroup NOTIFICATION-GROUP
		NOTIFICATIONS {cav3000p01v1NoAnalogTrap, cav3000p01v1AnalogUnlockTrap, cav3000p01v1AnalogOvldTrap }
			STATUS current
			DESCRIPTION
				"Module CAV3000P01V1 Trap Group"
			::= { trapGroup 157401 }

		-- 1.3.6.1.4.1.10106.2.3.2.157501
		cav3001p01v1TrapGroup NOTIFICATION-GROUP
		NOTIFICATIONS {cav3001p01v1NoSdiTrap, cav3001p01v1SdiUnlockTrap, cav3001p01v1EdhFullErrTrap, cav3001p01v1EdhActErrTrap }
			STATUS current
			DESCRIPTION
				"Module CAV3001P01V1 Trap Group"
			::= { trapGroup 157501 }

		-- 1.3.6.1.4.1.10106.2.3.2.157601
		cav3002p01v1TrapGroup NOTIFICATION-GROUP
		NOTIFICATIONS {cav3002p01v1NoAnalogTrap, cav3002p01v1AnalogUnlockTrap, cav3002p01v1AnalogOvldTrap, cav3002p01v1NoSdiTrap, cav3002p01v1SdiUnlockTrap, 
				cav3002p01v1EdhFullErrTrap, cav3002p01v1EdhActErrTrap }
			STATUS current
			DESCRIPTION
				"Module CAV3002P01V1 Trap Group"
			::= { trapGroup 157601 }

		-- 1.3.6.1.4.1.10106.2.3.2.162801
		dsw3000c03v1TrapGroup NOTIFICATION-GROUP
		NOTIFICATIONS {dsw3000c03v1ModeTrap, dsw3000c03v1InputTrap, dsw3000c03v1MainFailTrap, dsw3000c03v1ExtMainFailTrap, dsw3000c03v1ResFailTrap, 
				dsw3000c03v1ExtResFailTrap, dsw3000c03v1AuxFailTrap, dsw3000c03v1ExtAuxFailTrap }
			STATUS current
			DESCRIPTION
				"Module DSW3000C03V1 Trap Group"
			::= { trapGroup 162801 }

		-- 1.3.6.1.4.1.10106.2.3.2.163501
		eap3000p01v1TrapGroup NOTIFICATION-GROUP
		NOTIFICATIONS {eap3000p01v1NoSigTrap, eap3000p01v1Antiph12Trap, eap3000p01v1Antiph34Trap, eap3000p01v1SilCh1Trap, eap3000p01v1SilCh2Trap, 
				eap3000p01v1SilCh3Trap, eap3000p01v1SilCh4Trap, eap3000p01v1OvlCh1Trap, eap3000p01v1OvlCh2Trap, eap3000p01v1OvlCh3Trap, 
				eap3000p01v1OvlCh4Trap }
			STATUS current
			DESCRIPTION
				"Module EAP3000P01V1 Trap Group"
			::= { trapGroup 163501 }

		-- 1.3.6.1.4.1.10106.2.3.2.166801
		txe3000p01v1TrapGroup NOTIFICATION-GROUP
		NOTIFICATIONS {txe3000p01v1NoSignalTrap }
			STATUS current
			DESCRIPTION
				"Module TXE3000P01V1 Trap Group"
			::= { trapGroup 166801 }

		-- 1.3.6.1.4.1.10106.2.3.2.166802
		txe3000p01v2TrapGroup NOTIFICATION-GROUP
		NOTIFICATIONS {txe3000p01v2NoSignalTrap }
			STATUS current
			DESCRIPTION
				"Module TXE3000P01V2 Trap Group"
			::= { trapGroup 166802 }

		-- 1.3.6.1.4.1.10106.2.3.2.166901
		txd3000p01v1TrapGroup NOTIFICATION-GROUP
		NOTIFICATIONS {txd3000p01v1NoSignalTrap }
			STATUS current
			DESCRIPTION
				"Module TXD3000P01V1 Trap Group"
			::= { trapGroup 166901 }

		-- 1.3.6.1.4.1.10106.2.3.2.166902
		txd3000p01v2TrapGroup NOTIFICATION-GROUP
		NOTIFICATIONS {txd3000p01v2NoSignalTrap }
			STATUS current
			DESCRIPTION
				"Module TXD3000P01V2 Trap Group"
			::= { trapGroup 166902 }

		-- 1.3.6.1.4.1.10106.2.3.2.167201
		vfd3000c01v1TrapGroup NOTIFICATION-GROUP
		NOTIFICATIONS {vfd3000c01v1MainOutInputTrap, vfd3000c01v1OutInputTrap, vfd3000c01v1MaxEqMTrap, vfd3000c01v1BadFmtMTrap, vfd3000c01v1EdhErrMTrap, 
				vfd3000c01v1BlackMTrap, vfd3000c01v1FreezeMTrap, vfd3000c01v1MaxEqRTrap, vfd3000c01v1BadFmtRTrap, vfd3000c01v1EdhErrRTrap, 
				vfd3000c01v1BlackRTrap, vfd3000c01v1FreezeRTrap }
			STATUS current
			DESCRIPTION
				"Module VFD3000C01V1 Trap Group"
			::= { trapGroup 167201 }

		-- 1.3.6.1.4.1.10106.2.3.2.167501
		dar3000p01v1TrapGroup NOTIFICATION-GROUP
		NOTIFICATIONS {dar3000p01v1UnlockAesTrap, dar3000p01v1UnlockVidTrap, dar3000p01v1UnlockWclkTrap, dar3000p01v1NoAesTrap, dar3000p01v1NoVidTrap, 
				dar3000p01v1NoWclkTrap }
			STATUS current
			DESCRIPTION
				"Module DAR3000P01V1 Trap Group"
			::= { trapGroup 167501 }

		-- 1.3.6.1.4.1.10106.2.3.2.184801
		txt3000p01v1TrapGroup NOTIFICATION-GROUP
		NOTIFICATIONS {txt3000p01v1NoSigPgmTrap, txt3000p01v1NoSigSrcTrap }
			STATUS current
			DESCRIPTION
				"Module TXT3000P01V1 Trap Group"
			::= { trapGroup 184801 }

		-- 1.3.6.1.4.1.10106.2.3.2.195701
		gps3000p01v1TrapGroup NOTIFICATION-GROUP
		NOTIFICATIONS {gps3000p01v1HoldoverTrap, gps3000p01v1HoldoverStatTrap, gps3000p01v1RedundFailTrap, gps3000p01v1OutputsMutedTrap, gps3000p01v1AntenaStatTrap }
			STATUS current
			DESCRIPTION
				"Module GPS3000P01V1 Trap Group"
			::= { trapGroup 195701 }

		-- 1.3.6.1.4.1.10106.2.3.2.195702
		gps3000p01v2TrapGroup NOTIFICATION-GROUP
		NOTIFICATIONS {gps3000p01v2HoldoverTrap, gps3000p01v2HoldoverStatTrap, gps3000p01v2RedundFailTrap, gps3000p01v2OutputsMutedTrap, gps3000p01v2AntenaStatTrap }
			STATUS current
			DESCRIPTION
				"Module GPS3000P01V2 Trap Group"
			::= { trapGroup 195702 }

		-- 1.3.6.1.4.1.10106.2.3.2.195703
		gps3000p01v3TrapGroup NOTIFICATION-GROUP
		NOTIFICATIONS {gps3000p01v3HoldoverTrap, gps3000p01v3HoldoverStatTrap, gps3000p01v3RedundFailTrap, gps3000p01v3OutputsMutedTrap, gps3000p01v3AntenaStatTrap }
			STATUS current
			DESCRIPTION
				"Module GPS3000P01V3 Trap Group"
			::= { trapGroup 195703 }

		-- 1.3.6.1.4.1.10106.2.3.2.195704
		gps3000p01v4TrapGroup NOTIFICATION-GROUP
		NOTIFICATIONS {gps3000p01v4HoldoverTrap, gps3000p01v4HoldoverStatTrap, gps3000p01v4RedundFailTrap, gps3000p01v4OutputsMutedTrap, gps3000p01v4AntenaStatTrap }
			STATUS current
			DESCRIPTION
				"Module GPS3000P01V4 Trap Group"
			::= { trapGroup 195704 }

		-- 1.3.6.1.4.1.10106.2.3.2.207201
		sdt3000p01v1TrapGroup NOTIFICATION-GROUP
		NOTIFICATIONS {sdt3000p01v1NoSigATrap, sdt3000p01v1LaserFailATrap, sdt3000p01v1NoSigBTrap, sdt3000p01v1LaserFailBTrap }
			STATUS current
			DESCRIPTION
				"Module SDT3000P01V1 Trap Group"
			::= { trapGroup 207201 }

		-- 1.3.6.1.4.1.10106.2.3.2.207301
		sdr3000p01v1TrapGroup NOTIFICATION-GROUP
		NOTIFICATIONS {sdr3000p01v1NoSigATrap, sdr3000p01v1NoSigBTrap }
			STATUS current
			DESCRIPTION
				"Module SDR3000P01V1 Trap Group"
			::= { trapGroup 207301 }

		-- 1.3.6.1.4.1.10106.2.3.2.211201
		dsw3000p05v1TrapGroup NOTIFICATION-GROUP
		NOTIFICATIONS {dsw3000p05v1ModeTrap, dsw3000p05v1InputTrap, dsw3000p05v1MainFailTrap, dsw3000p05v1ExtMainFailTrap, dsw3000p05v1ResFailTrap, 
				dsw3000p05v1ExtResFailTrap, dsw3000p05v1AuxFailTrap, dsw3000p05v1ExtAuxFailTrap }
			STATUS current
			DESCRIPTION
				"Module DSW3000P05V1 Trap Group"
			::= { trapGroup 211201 }

		-- 1.3.6.1.4.1.10106.2.3.2.213201
		gps3000p02v1TrapGroup NOTIFICATION-GROUP
		NOTIFICATIONS {gps3000p02v1HoldoverTrap, gps3000p02v1HoldoverStatTrap, gps3000p02v1RedundFailTrap, gps3000p02v1OutputsMutedTrap, gps3000p02v1AntenaStatTrap }
			STATUS current
			DESCRIPTION
				"Module GPS3000P02V1 Trap Group"
			::= { trapGroup 213201 }

		-- 1.3.6.1.4.1.10106.2.3.2.213202
		gps3000p02v2TrapGroup NOTIFICATION-GROUP
		NOTIFICATIONS {gps3000p02v2HoldoverTrap, gps3000p02v2HoldoverStatTrap, gps3000p02v2RedundFailTrap, gps3000p02v2OutputsMutedTrap, gps3000p02v2AntenaStatTrap }
			STATUS current
			DESCRIPTION
				"Module GPS3000P02V2 Trap Group"
			::= { trapGroup 213202 }

		-- 1.3.6.1.4.1.10106.2.3.2.213203
		gps3000p02v3TrapGroup NOTIFICATION-GROUP
		NOTIFICATIONS {gps3000p02v3HoldoverTrap, gps3000p02v3HoldoverStatTrap, gps3000p02v3RedundFailTrap, gps3000p02v3OutputsMutedTrap, gps3000p02v3AntenaStatTrap }
			STATUS current
			DESCRIPTION
				"Module GPS3000P02V3 Trap Group"
			::= { trapGroup 213203 }

		-- 1.3.6.1.4.1.10106.2.3.2.213204
		gps3000p02v4TrapGroup NOTIFICATION-GROUP
		NOTIFICATIONS {gps3000p02v4HoldoverTrap, gps3000p02v4HoldoverStatTrap, gps3000p02v4RedundFailTrap, gps3000p02v4OutputsMutedTrap, gps3000p02v4AntenaStatTrap }
			STATUS current
			DESCRIPTION
				"Module GPS3000P02V4 Trap Group"
			::= { trapGroup 213204 }

		-- 1.3.6.1.4.1.10106.2.3.2.215401
		pds3001p01v1TrapGroup NOTIFICATION-GROUP
		NOTIFICATIONS {pds3001p01v1UnlockTrap, pds3001p01v1BlackTrap, pds3001p01v1FreezeTrap, pds3001p01v1UnlockTTrap, pds3001p01v1BlackTTrap, 
				pds3001p01v1FreezeTTrap, pds3001p01v1OverloadTrap }
			STATUS current
			DESCRIPTION
				"Module PDS3001P01V1 Trap Group"
			::= { trapGroup 215401 }

		-- 1.3.6.1.4.1.10106.2.3.2.216401
		gps3000p03v1TrapGroup NOTIFICATION-GROUP
		NOTIFICATIONS {gps3000p03v1HoldoverTrap, gps3000p03v1HoldoverStatTrap, gps3000p03v1RedundFailTrap, gps3000p03v1OutputsMutedTrap, gps3000p03v1AntenaStatTrap }
			STATUS current
			DESCRIPTION
				"Module GPS3000P03V1 Trap Group"
			::= { trapGroup 216401 }

		-- 1.3.6.1.4.1.10106.2.3.2.216402
		gps3000p03v2TrapGroup NOTIFICATION-GROUP
		NOTIFICATIONS {gps3000p03v2HoldoverTrap, gps3000p03v2HoldoverStatTrap, gps3000p03v2RedundFailTrap, gps3000p03v2OutputsMutedTrap, gps3000p03v2AntenaStatTrap }
			STATUS current
			DESCRIPTION
				"Module GPS3000P03V2 Trap Group"
			::= { trapGroup 216402 }

		-- 1.3.6.1.4.1.10106.2.3.2.216403
		gps3000p03v3TrapGroup NOTIFICATION-GROUP
		NOTIFICATIONS {gps3000p03v3HoldoverTrap, gps3000p03v3HoldoverStatTrap, gps3000p03v3RedundFailTrap, gps3000p03v3OutputsMutedTrap, gps3000p03v3AntenaStatTrap }
			STATUS current
			DESCRIPTION
				"Module GPS3000P03V3 Trap Group"
			::= { trapGroup 216403 }

		-- 1.3.6.1.4.1.10106.2.3.2.216404
		gps3000p03v4TrapGroup NOTIFICATION-GROUP
		NOTIFICATIONS {gps3000p03v4HoldoverTrap, gps3000p03v4HoldoverStatTrap, gps3000p03v4RedundFailTrap, gps3000p03v4OutputsMutedTrap, gps3000p03v4AntenaStatTrap }
			STATUS current
			DESCRIPTION
				"Module GPS3000P03V4 Trap Group"
			::= { trapGroup 216404 }

		-- 1.3.6.1.4.1.10106.2.3.2.224701
		frs3004c02v1TrapGroup NOTIFICATION-GROUP
		NOTIFICATIONS {frs3004c02v1NoRefTrap, frs3004c02v1RefUnlockTrap, frs3004c02v1NoSig1Trap, frs3004c02v1NoSig2Trap, frs3004c02v1NoSig3Trap, 
				frs3004c02v1NoSig4Trap }
			STATUS current
			DESCRIPTION
				"Module FRS3004C02V1 Trap Group"
			::= { trapGroup 224701 }

		-- 1.3.6.1.4.1.10106.2.3.2.229601
		dvd3001p01v1TrapGroup NOTIFICATION-GROUP
		NOTIFICATIONS {dvd3001p01v1NoSigATrap, dvd3001p01v1NoSigBTrap }
			STATUS current
			DESCRIPTION
				"Module DVD3001P01V1 Trap Group"
			::= { trapGroup 229601 }

		-- 1.3.6.1.4.1.10106.2.3.2.232401
		frs3004c01v1TrapGroup NOTIFICATION-GROUP
		NOTIFICATIONS {frs3004c01v1NoRefTrap, frs3004c01v1RefUnlockTrap, frs3004c01v1NoSig1Trap, frs3004c01v1NoSig2Trap, frs3004c01v1NoSig3Trap, 
				frs3004c01v1NoSig4Trap }
			STATUS current
			DESCRIPTION
				"Module FRS3004C01V1 Trap Group"
			::= { trapGroup 232401 }

		-- 1.3.6.1.4.1.10106.2.3.2.233401
		dvd3001c02v1TrapGroup NOTIFICATION-GROUP
		NOTIFICATIONS {dvd3001c02v1NoSigATrap, dvd3001c02v1NoSigBTrap }
			STATUS current
			DESCRIPTION
				"Module DVD3001C02V1 Trap Group"
			::= { trapGroup 233401 }

		-- 1.3.6.1.4.1.10106.2.3.2.233501
		dvd3001c03v1TrapGroup NOTIFICATION-GROUP
		NOTIFICATIONS {dvd3001c03v1NoSigATrap, dvd3001c03v1NoSigBTrap }
			STATUS current
			DESCRIPTION
				"Module DVD3001C03V1 Trap Group"
			::= { trapGroup 233501 }

		-- 1.3.6.1.4.1.10106.2.3.2.234101
		dvd3001c04v1TrapGroup NOTIFICATION-GROUP
		NOTIFICATIONS {dvd3001c04v1NoSigATrap }
			STATUS current
			DESCRIPTION
				"Module DVD3001C04V1 Trap Group"
			::= { trapGroup 234101 }

		-- 1.3.6.1.4.1.10106.2.3.2.234201
		dvd3001c05v1TrapGroup NOTIFICATION-GROUP
		NOTIFICATIONS {dvd3001c05v1NoSigATrap }
			STATUS current
			DESCRIPTION
				"Module DVD3001C05V1 Trap Group"
			::= { trapGroup 234201 }

		-- 1.3.6.1.4.1.10106.2.3.2.238701
		sdr3000p02v1TrapGroup NOTIFICATION-GROUP
		NOTIFICATIONS {sdr3000p02v1NoSigATrap, sdr3000p02v1NoSigBTrap }
			STATUS current
			DESCRIPTION
				"Module SDR3000P02V1 Trap Group"
			::= { trapGroup 238701 }

		-- 1.3.6.1.4.1.10106.2.3.2.241501
		asw3000c01v1TrapGroup NOTIFICATION-GROUP
		NOTIFICATIONS {asw3000c01v1ModeTrap, asw3000c01v1InputTrap, asw3000c01v1MainGlobalFailTrap, asw3000c01v1ResGlobalFailTrap, asw3000c01v1MainGpiFailTrap, 
				asw3000c01v1MainPresFailTrap, asw3000c01v1MainSyncLFailTrap, asw3000c01v1MainSyncBFailTrap, asw3000c01v1MainPatErFailTrap, asw3000c01v1MainPatCcFailTrap, 
				asw3000c01v1MainTraffFailTrap, asw3000c01v1MainNullPFailTrap, asw3000c01v1ResGpiFailTrap, asw3000c01v1ResPresFailTrap, asw3000c01v1ResSyncLFailTrap, 
				asw3000c01v1ResSyncBFailTrap, asw3000c01v1ResPatErFailTrap, asw3000c01v1ResPatCcFailTrap, asw3000c01v1ResTraffFailTrap, asw3000c01v1ResNullPFailTrap }
			STATUS current
			DESCRIPTION
				"Module ASW3000C01V1 Trap Group"
			::= { trapGroup 241501 }

		-- 1.3.6.1.4.1.10106.2.3.2.245601
		adl3000c01v1TrapGroup NOTIFICATION-GROUP
		NOTIFICATIONS {adl3000c01v1GlobalFailTrap }
			STATUS current
			DESCRIPTION
				"Module ADL3000C01V1 Trap Group"
			::= { trapGroup 245601 }

		-- 1.3.6.1.4.1.10106.2.3.2.247001
		hvd3000c01v1TrapGroup NOTIFICATION-GROUP
		NOTIFICATIONS {hvd3000c01v1NoSigATrap, hvd3000c01v1UnlockATrap, hvd3000c01v1NoSigBTrap, hvd3000c01v1UnlockBTrap }
			STATUS current
			DESCRIPTION
				"Module HVD3000C01V1 Trap Group"
			::= { trapGroup 247001 }

		-- 1.3.6.1.4.1.10106.2.3.2.247002
		hvd3000c01v2TrapGroup NOTIFICATION-GROUP
		NOTIFICATIONS {hvd3000c01v2NoSigATrap, hvd3000c01v2UnlockATrap, hvd3000c01v2NoSigBTrap, hvd3000c01v2UnlockBTrap }
			STATUS current
			DESCRIPTION
				"Module HVD3000C01V2 Trap Group"
			::= { trapGroup 247002 }

		-- 1.3.6.1.4.1.10106.2.3.2.247101
		hdt3000c01v1TrapGroup NOTIFICATION-GROUP
		NOTIFICATIONS {hdt3000c01v1NoSigATrap, hdt3000c01v1UnlockATrap, hdt3000c01v1LaserFailATrap, hdt3000c01v1NoSigBTrap, hdt3000c01v1UnlockBTrap, 
				hdt3000c01v1LaserFailBTrap }
			STATUS current
			DESCRIPTION
				"Module HDT3000C01V1 Trap Group"
			::= { trapGroup 247101 }

		-- 1.3.6.1.4.1.10106.2.3.2.247201
		hdr3000c01v1TrapGroup NOTIFICATION-GROUP
		NOTIFICATIONS {hdr3000c01v1NoSigEATrap, hdr3000c01v1NoSigEOATrap, hdr3000c01v1UnlockATrap, hdr3000c01v1NoSigEBTrap, hdr3000c01v1NoSigOBTrap, 
				hdr3000c01v1UnlockBTrap }
			STATUS current
			DESCRIPTION
				"Module HDR3000C01V1 Trap Group"
			::= { trapGroup 247201 }

		-- 1.3.6.1.4.1.10106.2.3.2.259501
		dli3001c01v1TrapGroup NOTIFICATION-GROUP
		NOTIFICATIONS {dli3001c01v1NoSigTrap, dli3001c01v1AudioFr0ErrTrap, dli3001c01v1AudioFr1ErrTrap }
			STATUS current
			DESCRIPTION
				"Module DLI3001C01V1 Trap Group"
			::= { trapGroup 259501 }

		-- 1.3.6.1.4.1.10106.2.3.2.259601
		eap3001c01v1TrapGroup NOTIFICATION-GROUP
		NOTIFICATIONS {eap3001c01v1NoSigATrap, eap3001c01v1AudioFr0ErrATrap, eap3001c01v1AudioFr1ErrATrap, eap3001c01v1NoSigBTrap, eap3001c01v1AudioFr0ErrBTrap, 
				eap3001c01v1AudioFr1ErrBTrap }
			STATUS current
			DESCRIPTION
				"Module EAP3001C01V1 Trap Group"
			::= { trapGroup 259601 }

		-- 1.3.6.1.4.1.10106.2.3.2.272801
		ur-3100r05v1TrapGroup NOTIFICATION-GROUP
		NOTIFICATIONS {ur-3100r05v1PwrFailRTrap, ur-3100r05v1PwrFailLTrap }
			STATUS current
			DESCRIPTION
				"Module UR-3100R05V1 Trap Group"
			::= { trapGroup 272801 }

		-- 1.3.6.1.4.1.10106.2.3.2.272901
		ur-3100r06v1TrapGroup NOTIFICATION-GROUP
		NOTIFICATIONS {ur-3100r06v1PwrFailRTrap, ur-3100r06v1PwrFailLTrap }
			STATUS current
			DESCRIPTION
				"Module UR-3100R06V1 Trap Group"
			::= { trapGroup 272901 }

		-- 1.3.6.1.4.1.10106.2.3.2.273001
		ur-3100r07v1TrapGroup NOTIFICATION-GROUP
		NOTIFICATIONS {ur-3100r07v1PwrFailRTrap, ur-3100r07v1PwrFailLTrap }
			STATUS current
			DESCRIPTION
				"Module UR-3100R07V1 Trap Group"
			::= { trapGroup 273001 }

		-- 1.3.6.1.4.1.10106.2.3.2.273101
		ur-3100r08v1TrapGroup NOTIFICATION-GROUP
		NOTIFICATIONS {ur-3100r08v1PwrFailRTrap, ur-3100r08v1PwrFailLTrap }
			STATUS current
			DESCRIPTION
				"Module UR-3100R08V1 Trap Group"
			::= { trapGroup 273101 }

		-- 1.3.6.1.4.1.10106.2.3.2.273201
		ur-3100r09v1TrapGroup NOTIFICATION-GROUP
		NOTIFICATIONS {ur-3100r09v1PwrFailRTrap, ur-3100r09v1PwrFailLTrap }
			STATUS current
			DESCRIPTION
				"Module UR-3100R09V1 Trap Group"
			::= { trapGroup 273201 }

		-- 1.3.6.1.4.1.10106.2.3.2.274401
		dvm3001c01v1TrapGroup NOTIFICATION-GROUP
		NOTIFICATIONS {dvm3001c01v1NoSigATrap, dvm3001c01v1NoSigBTrap, dvm3001c01v1UnlockATrap, dvm3001c01v1UnlockBTrap }
			STATUS current
			DESCRIPTION
				"Module DVM3001C01V1 Trap Group"
			::= { trapGroup 274401 }

		-- 1.3.6.1.4.1.10106.2.3.2.275101
		dsw3001c01v1TrapGroup NOTIFICATION-GROUP
		NOTIFICATIONS {dsw3001c01v1ModeTrap, dsw3001c01v1InputTrap, dsw3001c01v1VideoFailMTrap, dsw3001c01v1VideoFailRTrap, dsw3001c01v1AudioFailMTrap, 
				dsw3001c01v1AudioFailRTrap }
			STATUS current
			DESCRIPTION
				"Module DSW3001C01V1 Trap Group"
			::= { trapGroup 275101 }

		-- 1.3.6.1.4.1.10106.2.3.2.278601
		dvb3001c01v1TrapGroup NOTIFICATION-GROUP
		NOTIFICATIONS {dvb3001c01v1NoSigATrap, dvb3001c01v1NoSigBTrap }
			STATUS current
			DESCRIPTION
				"Module DVB3001C01V1 Trap Group"
			::= { trapGroup 278601 }

		-- 1.3.6.1.4.1.10106.2.3.2.282401
		dvm3001c02v1TrapGroup NOTIFICATION-GROUP
		NOTIFICATIONS {dvm3001c02v1NoSigATrap, dvm3001c02v1NoSigBTrap, dvm3001c02v1UnlockATrap, dvm3001c02v1UnlockBTrap }
			STATUS current
			DESCRIPTION
				"Module DVM3001C02V1 Trap Group"
			::= { trapGroup 282401 }

		-- 1.3.6.1.4.1.10106.2.3.2.283901
		dvb3001c02v1TrapGroup NOTIFICATION-GROUP
		NOTIFICATIONS {dvb3001c02v1NoSigATrap, dvb3001c02v1NoSigBTrap }
			STATUS current
			DESCRIPTION
				"Module DVB3001C02V1 Trap Group"
			::= { trapGroup 283901 }

		-- 1.3.6.1.4.1.10106.2.3.2.286201
		gps3002c01v1TrapGroup NOTIFICATION-GROUP
		NOTIFICATIONS {gps3002c01v1RedundanceModeTrap, gps3002c01v1HoldoverStatTrap, gps3002c01v1MaintenanceFailTrap, gps3002c01v1OutputsMutedTrap, gps3002c01v11ppsDisableTrap, 
				gps3002c01v1AntenaStatTrap }
			STATUS current
			DESCRIPTION
				"Module GPS3002C01V1 Trap Group"
			::= { trapGroup 286201 }

		-- 1.3.6.1.4.1.10106.2.3.2.290701
		gps3002c03v1TrapGroup NOTIFICATION-GROUP
		NOTIFICATIONS {gps3002c03v1RedundanceModeTrap, gps3002c03v1HoldoverStatTrap, gps3002c03v1MaintenanceFailTrap, gps3002c03v1OutputsMutedTrap, gps3002c03v11ppsDisableTrap, 
				gps3002c03v1AntenaStatTrap }
			STATUS current
			DESCRIPTION
				"Module GPS3002C03V1 Trap Group"
			::= { trapGroup 290701 }

		-- 1.3.6.1.4.1.10106.2.3.2.290901
		tsm3001c01v1TrapGroup NOTIFICATION-GROUP
		NOTIFICATIONS {tsm3001c01v1NoTsNatTrap, tsm3001c01v1NoReplacTrap, tsm3001c01v1BadTsidNatTrap, tsm3001c01v1NoTsRegTrap, tsm3001c01v1BadTsidRegTrap }
			STATUS current
			DESCRIPTION
				"Module TSM3001C01V1 Trap Group"
			::= { trapGroup 290901 }

		-- 1.3.6.1.4.1.10106.2.3.2.315301
		dsw3000c05v1TrapGroup NOTIFICATION-GROUP
		NOTIFICATIONS {dsw3000c05v1ModeTrap, dsw3000c05v1InputTrap, dsw3000c05v1MainFailTrap, dsw3000c05v1ExtMainFailTrap, dsw3000c05v1ResFailTrap, 
				dsw3000c05v1ExtResFailTrap, dsw3000c05v1AuxFailTrap, dsw3000c05v1ExtAuxFailTrap }
			STATUS current
			DESCRIPTION
				"Module DSW3000C05V1 Trap Group"
			::= { trapGroup 315301 }

		-- 1.3.6.1.4.1.10106.2.3.2.316801
		ssw3000c01v1TrapGroup NOTIFICATION-GROUP
		NOTIFICATIONS {ssw3000c01v1ModeTrap, ssw3000c01v1DvbTModeTrap, ssw3000c01v1InputTrap, ssw3000c01v1OutDelayTrap, ssw3000c01v1MainFailTrap, 
				ssw3000c01v1ExtMainFailTrap, ssw3000c01v1ResFailTrap, ssw3000c01v1ExtResFailTrap, ssw3000c01v1AuxFailTrap, ssw3000c01v1ExtAuxFailTrap, 
				ssw3000c01v11ppsFailTrap, ssw3000c01v1GlobalSeamTrap }
			STATUS current
			DESCRIPTION
				"Module SSW3000C01V1 Trap Group"
			::= { trapGroup 316801 }

		-- 1.3.6.1.4.1.10106.2.3.2.320501
		pdc3002c01v1TrapGroup NOTIFICATION-GROUP
		NOTIFICATIONS {pdc3002c01v1UnlockATrap, pdc3002c01v1UnlockBTrap, pdc3002c01v1NoSigATrap, pdc3002c01v1NoSigBTrap }
			STATUS current
			DESCRIPTION
				"Module PDC3002C01V1 Trap Group"
			::= { trapGroup 320501 }

		-- 1.3.6.1.4.1.10106.2.3.2.324201
		vct3000c11v1TrapGroup NOTIFICATION-GROUP
		NOTIFICATIONS {vct3000c11v1ModeTrap, vct3000c11v1InputTrap, vct3000c11v1MainFailTrap, vct3000c11v1ResFailTrap, vct3000c11v1AuxFailTrap }
			STATUS current
			DESCRIPTION
				"Module VCT3000C11V1 Trap Group"
			::= { trapGroup 324201 }

		-- 1.3.6.1.4.1.10106.2.3.2.324301
		vct3000c12v1TrapGroup NOTIFICATION-GROUP
		NOTIFICATIONS {vct3000c12v1ModeTrap, vct3000c12v1InputTrap, vct3000c12v1MainFailTrap, vct3000c12v1ResFailTrap, vct3000c12v1AuxFailTrap }
			STATUS current
			DESCRIPTION
				"Module VCT3000C12V1 Trap Group"
			::= { trapGroup 324301 }

		-- 1.3.6.1.4.1.10106.2.3.2.324401
		vct3000c14v1TrapGroup NOTIFICATION-GROUP
		NOTIFICATIONS {vct3000c14v1ModeTrap, vct3000c14v1InputTrap, vct3000c14v1MainFailTrap, vct3000c14v1ResFailTrap, vct3000c14v1AuxFailTrap }
			STATUS current
			DESCRIPTION
				"Module VCT3000C14V1 Trap Group"
			::= { trapGroup 324401 }

		-- 1.3.6.1.4.1.10106.2.3.2.324501
		vct3000c15v1TrapGroup NOTIFICATION-GROUP
		NOTIFICATIONS {vct3000c15v1ModeTrap, vct3000c15v1InputTrap, vct3000c15v1MainFailTrap, vct3000c15v1ResFailTrap, vct3000c15v1AuxFailTrap }
			STATUS current
			DESCRIPTION
				"Module VCT3000C15V1 Trap Group"
			::= { trapGroup 324501 }

		-- 1.3.6.1.4.1.10106.2.3.2.327001
		vtl3000c01v1TrapGroup NOTIFICATION-GROUP
		NOTIFICATIONS {vtl3000c01v1NoSignalTrap, vtl3000c01v1DupTcTrap, vtl3000c01v1LostTcTrap, vtl3000c01v1NoTcFrameTrap }
			STATUS current
			DESCRIPTION
				"Module VTL3000C01V1 Trap Group"
			::= { trapGroup 327001 }

		-- 1.3.6.1.4.1.10106.2.3.2.328401
		tle3001c01v1TrapGroup NOTIFICATION-GROUP
		NOTIFICATIONS {tle3001c01v1Gpi1Trap, tle3001c01v1Gpi2Trap, tle3001c01v1Gpi3Trap, tle3001c01v1Gpi4Trap, tle3001c01v1RedBoardTrap, 
				tle3001c01v1EthLinkTrap, tle3001c01v1EthRedActTrap }
			STATUS current
			DESCRIPTION
				"Module TLE3001C01V1 Trap Group"
			::= { trapGroup 328401 }

		-- 1.3.6.1.4.1.10106.2.3.2.339901
		gvd3000c01v1TrapGroup NOTIFICATION-GROUP
		NOTIFICATIONS {gvd3000c01v1LosATrap, gvd3000c01v1AisATrap, gvd3000c01v1LosBTrap, gvd3000c01v1AisBTrap }
			STATUS current
			DESCRIPTION
				"Module GVD3000C01V1 Trap Group"
			::= { trapGroup 339901 }

		-- 1.3.6.1.4.1.10106.2.3.2.343901
		htg3000c01v1TrapGroup NOTIFICATION-GROUP
		NOTIFICATIONS {htg3000c01v1RefLckFailTrap, htg3000c01v1RefFailTrap }
			STATUS current
			DESCRIPTION
				"Module HTG3000C01V1 Trap Group"
			::= { trapGroup 343901 }

		-- 1.3.6.1.4.1.10106.2.3.2.347601
		hvd3001c01v1TrapGroup NOTIFICATION-GROUP
		NOTIFICATIONS {hvd3001c01v1NoSigATrap, hvd3001c01v1UnlockATrap, hvd3001c01v1LFailATrap, hvd3001c01v1NoSigBTrap, hvd3001c01v1UnlockBTrap, 
				hvd3001c01v1LFailBTrap }
			STATUS current
			DESCRIPTION
				"Module HVD3001C01V1 Trap Group"
			::= { trapGroup 347601 }

		-- 1.3.6.1.4.1.10106.2.3.2.350401
		vct3000c13v1TrapGroup NOTIFICATION-GROUP
		NOTIFICATIONS {vct3000c13v1ModeTrap, vct3000c13v1InputTrap, vct3000c13v1MainFailTrap, vct3000c13v1ResFailTrap, vct3000c13v1AuxFailTrap }
			STATUS current
			DESCRIPTION
				"Module VCT3000C13V1 Trap Group"
			::= { trapGroup 350401 }

		-- 1.3.6.1.4.1.10106.2.3.2.352201
		dad3002c02v1TrapGroup NOTIFICATION-GROUP
		NOTIFICATIONS {dad3002c02v1LosATrap, dad3002c02v1LosBTrap }
			STATUS current
			DESCRIPTION
				"Module DAD3002C02V1 Trap Group"
			::= { trapGroup 352201 }

		-- 1.3.6.1.4.1.10106.2.3.2.353101
		hvd3001c02v1TrapGroup NOTIFICATION-GROUP
		NOTIFICATIONS {hvd3001c02v1NoSigATrap, hvd3001c02v1UnlockATrap, hvd3001c02v1LFailATrap, hvd3001c02v1NoSigBTrap, hvd3001c02v1UnlockBTrap, 
				hvd3001c02v1LFailBTrap }
			STATUS current
			DESCRIPTION
				"Module HVD3001C02V1 Trap Group"
			::= { trapGroup 353101 }

		-- 1.3.6.1.4.1.10106.2.3.2.357101
		hvd3001c03v1TrapGroup NOTIFICATION-GROUP
		NOTIFICATIONS {hvd3001c03v1NoSigATrap, hvd3001c03v1UnlockATrap, hvd3001c03v1LFailATrap, hvd3001c03v1NoSigBTrap, hvd3001c03v1UnlockBTrap, 
				hvd3001c03v1LFailBTrap }
			STATUS current
			DESCRIPTION
				"Module HVD3001C03V1 Trap Group"
			::= { trapGroup 357101 }

		-- 1.3.6.1.4.1.10106.2.3.2.357201
		hvd3001c04v1TrapGroup NOTIFICATION-GROUP
		NOTIFICATIONS {hvd3001c04v1NoSigATrap, hvd3001c04v1UnlockATrap, hvd3001c04v1LFailATrap, hvd3001c04v1NoSigBTrap, hvd3001c04v1UnlockBTrap, 
				hvd3001c04v1LFailBTrap }
			STATUS current
			DESCRIPTION
				"Module HVD3001C04V1 Trap Group"
			::= { trapGroup 357201 }

		-- 1.3.6.1.4.1.10106.2.3.2.357501
		hfs3000c01v1TrapGroup NOTIFICATION-GROUP
		NOTIFICATIONS {hfs3000c01v1NoSigATrap, hfs3000c01v1UnlockATrap, hfs3000c01v1EdhCrcATrap, hfs3000c01v1GpiFailATrap, hfs3000c01v1NoSigBTrap, 
				hfs3000c01v1UnlockBTrap, hfs3000c01v1EdhCrcBTrap, hfs3000c01v1GpiFailBTrap, hfs3000c01v1NoRefTrap, hfs3000c01v1RefAUnlockTrap, 
				hfs3000c01v1RefBUnlockTrap }
			STATUS current
			DESCRIPTION
				"Module HFS3000C01V1 Trap Group"
			::= { trapGroup 357501 }

		-- 1.3.6.1.4.1.10106.2.3.2.357502
		hfs3000c01v2TrapGroup NOTIFICATION-GROUP
		NOTIFICATIONS {hfs3000c01v2NoSigATrap, hfs3000c01v2UnlockATrap, hfs3000c01v2EdhCrcATrap, hfs3000c01v2GpiFailATrap, hfs3000c01v2NoSigBTrap, 
				hfs3000c01v2UnlockBTrap, hfs3000c01v2EdhCrcBTrap, hfs3000c01v2GpiFailBTrap, hfs3000c01v2NoRefTrap, hfs3000c01v2RefAUnlockTrap, 
				hfs3000c01v2RefBUnlockTrap }
			STATUS current
			DESCRIPTION
				"Module HFS3000C01V2 Trap Group"
			::= { trapGroup 357502 }

		-- 1.3.6.1.4.1.10106.2.3.2.358101
		hde3000c01v1TrapGroup NOTIFICATION-GROUP
		NOTIFICATIONS {hde3000c01v1NoSignalATrap, hde3000c01v1UnlockATrap, hde3000c01v1EdhErrorATrap, hde3000c01v1AesFailATrap, hde3000c01v1DeemFailATrap, 
				hde3000c01v1AesOvlATrap, hde3000c01v1DeemOvlATrap, hde3000c01v1NoSignalBTrap, hde3000c01v1UnlockBTrap, hde3000c01v1EdhErrorBTrap, 
				hde3000c01v1AesFailBTrap, hde3000c01v1DeemFailBTrap, hde3000c01v1AesOvlBTrap, hde3000c01v1DeemOvlBTrap }
			STATUS current
			DESCRIPTION
				"Module HDE3000C01V1 Trap Group"
			::= { trapGroup 358101 }

		-- 1.3.6.1.4.1.10106.2.3.2.359901
		hae3000c01v1TrapGroup NOTIFICATION-GROUP
		NOTIFICATIONS {hae3000c01v1NoSignalATrap, hae3000c01v1UnlockATrap, hae3000c01v1EdhErrorATrap, hae3000c01v1AesFailATrap, hae3000c01v1DeemFailATrap, 
				hae3000c01v1DeemOvlATrap, hae3000c01v1ClippingATrap, hae3000c01v1NoSignalBTrap, hae3000c01v1UnlockBTrap, hae3000c01v1EdhErrorBTrap, 
				hae3000c01v1AesFailBTrap, hae3000c01v1DeemFailBTrap, hae3000c01v1DeemOvlBTrap, hae3000c01v1ClippingBTrap }
			STATUS current
			DESCRIPTION
				"Module HAE3000C01V1 Trap Group"
			::= { trapGroup 359901 }

		-- 1.3.6.1.4.1.10106.2.3.2.360001
		had3000c01v1TrapGroup NOTIFICATION-GROUP
		NOTIFICATIONS {had3000c01v1NoSignalATrap, had3000c01v1UnlockATrap, had3000c01v1EdhErrorATrap, had3000c01v1SampRFailATrap, had3000c01v1DeemFailATrap, 
				had3000c01v1AesOvlATrap, had3000c01v1DeemOvlATrap, had3000c01v1NoSignalBTrap, had3000c01v1UnlockBTrap, had3000c01v1EdhErrorBTrap, 
				had3000c01v1SampRFailBTrap, had3000c01v1DeemFailBTrap, had3000c01v1AesOvlBTrap, had3000c01v1DeemOvlBTrap }
			STATUS current
			DESCRIPTION
				"Module HAD3000C01V1 Trap Group"
			::= { trapGroup 360001 }

		-- 1.3.6.1.4.1.10106.2.3.2.362001
		ipa3000c01v1TrapGroup NOTIFICATION-GROUP
		NOTIFICATIONS {ipa3000c01v1ModeTrap, ipa3000c01v1DvbTModeTrap, ipa3000c01v1InputTrap, ipa3000c01v1OutDelayTrap, ipa3000c01v11ppsFailTrap, 
				ipa3000c01v110mhzFailTrap, ipa3000c01v1OutputFailTrap, ipa3000c01v1AsiMainDelWarTrap, ipa3000c01v1AsiResDelWarTrap, ipa3000c01v1IpMainDelWarTrap, 
				ipa3000c01v1IpResDelWarTrap, ipa3000c01v1AsiMainFailTrap, ipa3000c01v1ExAsiMainFailTrap, ipa3000c01v1AsiResFailTrap, ipa3000c01v1ExAsiResFailTrap, 
				ipa3000c01v1IpMainFailTrap, ipa3000c01v1ExIpMainFailTrap, ipa3000c01v1IpResFailTrap, ipa3000c01v1ExIpResFailTrap, ipa3000c01v1GlobalSeamTrap }
			STATUS current
			DESCRIPTION
				"Module IPA3000C01V1 Trap Group"
			::= { trapGroup 362001 }

		-- 1.3.6.1.4.1.10106.2.3.2.362002
		ipa3000c01v2TrapGroup NOTIFICATION-GROUP
		NOTIFICATIONS {ipa3000c01v2ModeTrap, ipa3000c01v2DvbTModeTrap, ipa3000c01v2InputTrap, ipa3000c01v2OutDelayTrap, ipa3000c01v21ppsFailTrap, 
				ipa3000c01v210mhzFailTrap, ipa3000c01v2OutputFailTrap, ipa3000c01v2AsiMainDelWarTrap, ipa3000c01v2AsiResDelWarTrap, ipa3000c01v2IpMainDelWarTrap, 
				ipa3000c01v2IpResDelWarTrap, ipa3000c01v2AsiMainFailTrap, ipa3000c01v2ExAsiMainFailTrap, ipa3000c01v2AsiResFailTrap, ipa3000c01v2ExAsiResFailTrap, 
				ipa3000c01v2IpMainFailTrap, ipa3000c01v2ExIpMainFailTrap, ipa3000c01v2IpResFailTrap, ipa3000c01v2ExIpResFailTrap, ipa3000c01v2GlobalSeamTrap }
			STATUS current
			DESCRIPTION
				"Module IPA3000C01V2 Trap Group"
			::= { trapGroup 362002 }

		-- 1.3.6.1.4.1.10106.2.3.2.364801
		hsw3000c01v1TrapGroup NOTIFICATION-GROUP
		NOTIFICATIONS {hsw3000c01v1StateSelTrap, hsw3000c01v1SwitchModeTrap, hsw3000c01v1BypassEnableTrap, hsw3000c01v1OperatingModeTrap, hsw3000c01v1In1FailTrap, 
				hsw3000c01v1In2FailTrap, hsw3000c01v1In1ExtFailTrap, hsw3000c01v1In2ExtFailTrap, hsw3000c01v1BlindExtFailTrap, hsw3000c01v1SelOut1Trap, 
				hsw3000c01v1SelOut2Trap, hsw3000c01v1Gpi3StatTrap, hsw3000c01v1In1PhyFailTrap, hsw3000c01v1In1FmtFailTrap, hsw3000c01v1In1IncFailTrap, 
				hsw3000c01v1In1GpiFailTrap, hsw3000c01v1In1BlkFailTrap, hsw3000c01v1In1FrzFailTrap, hsw3000c01v1In1PatFailTrap, hsw3000c01v1In1CrcFailTrap, 
				hsw3000c01v1In2PhyFailTrap, hsw3000c01v1In2FmtFailTrap, hsw3000c01v1In2IncFailTrap, hsw3000c01v1In2GpiFailTrap, hsw3000c01v1In2BlkFailTrap, 
				hsw3000c01v1In2FrzFailTrap, hsw3000c01v1In2PatFailTrap, hsw3000c01v1In2CrcFailTrap, hsw3000c01v1RefFailTrap, hsw3000c01v1LockFailTrap }
			STATUS current
			DESCRIPTION
				"Module HSW3000C01V1 Trap Group"
			::= { trapGroup 364801 }

		-- 1.3.6.1.4.1.10106.2.3.2.364802
		hsw3000c01v2TrapGroup NOTIFICATION-GROUP
		NOTIFICATIONS {hsw3000c01v2StateSelTrap, hsw3000c01v2SwitchModeTrap, hsw3000c01v2BypassEnableTrap, hsw3000c01v2OperatingModeTrap, hsw3000c01v2In1FailTrap, 
				hsw3000c01v2In2FailTrap, hsw3000c01v2In1ExtFailTrap, hsw3000c01v2In2ExtFailTrap, hsw3000c01v2BlindExtFailTrap, hsw3000c01v2SelOut1Trap, 
				hsw3000c01v2SelOut2Trap, hsw3000c01v2Gpi3StatTrap, hsw3000c01v2In1PhyFailTrap, hsw3000c01v2In1FmtFailTrap, hsw3000c01v2In1IncFailTrap, 
				hsw3000c01v2In1GpiFailTrap, hsw3000c01v2In1BlkFailTrap, hsw3000c01v2In1FrzFailTrap, hsw3000c01v2In1PatFailTrap, hsw3000c01v2In1CrcFailTrap, 
				hsw3000c01v2In1SilFailTrap, hsw3000c01v2In1OvrFailTrap, hsw3000c01v2In1PhFailTrap, hsw3000c01v2In1PreFailTrap, hsw3000c01v2In2PhyFailTrap, 
				hsw3000c01v2In2FmtFailTrap, hsw3000c01v2In2IncFailTrap, hsw3000c01v2In2GpiFailTrap, hsw3000c01v2In2BlkFailTrap, hsw3000c01v2In2FrzFailTrap, 
				hsw3000c01v2In2PatFailTrap, hsw3000c01v2In2CrcFailTrap, hsw3000c01v2In2SilFailTrap, hsw3000c01v2In2OvrFailTrap, hsw3000c01v2In2PhFailTrap, 
				hsw3000c01v2In2PreFailTrap, hsw3000c01v2RefFailTrap, hsw3000c01v2LockFailTrap, hsw3000c01v2In1FormatTrap, hsw3000c01v2In2FormatTrap, 
				hsw3000c01v2RefFormatTrap, hsw3000c01v2EqualPidTrap, hsw3000c01v2EqualUmidTrap, hsw3000c01v2In1Grp1PresTrap, hsw3000c01v2In1Grp2PresTrap, 
				hsw3000c01v2In1Grp3PresTrap, hsw3000c01v2In1Grp4PresTrap, hsw3000c01v2In1Grp1P0ErrTrap, hsw3000c01v2In1Grp1P1ErrTrap, hsw3000c01v2In1Grp2P0ErrTrap, 
				hsw3000c01v2In1Grp2P1ErrTrap, hsw3000c01v2In1Grp3P0ErrTrap, hsw3000c01v2In1Grp3P1ErrTrap, hsw3000c01v2In1Grp4P0ErrTrap, hsw3000c01v2In1Grp4P1ErrTrap, 
				hsw3000c01v2In2Grp1PresTrap, hsw3000c01v2In2Grp2PresTrap, hsw3000c01v2In2Grp3PresTrap, hsw3000c01v2In2Grp4PresTrap, hsw3000c01v2In2Grp1P0ErrTrap, 
				hsw3000c01v2In2Grp1P1ErrTrap, hsw3000c01v2In2Grp2P0ErrTrap, hsw3000c01v2In2Grp2P1ErrTrap, hsw3000c01v2In2Grp3P0ErrTrap, hsw3000c01v2In2Grp3P1ErrTrap, 
				hsw3000c01v2In2Grp4P0ErrTrap, hsw3000c01v2In2Grp4P1ErrTrap }
			STATUS current
			DESCRIPTION
				"Module HSW3000C01V2 Trap Group"
			::= { trapGroup 364802 }

		-- 1.3.6.1.4.1.10106.2.3.2.364803
		hsw3000c01v3TrapGroup NOTIFICATION-GROUP
		NOTIFICATIONS {hsw3000c01v3StateSelTrap, hsw3000c01v3SwitchModeTrap, hsw3000c01v3BypassEnableTrap, hsw3000c01v3OperatingModeTrap, hsw3000c01v3In1FailTrap, 
				hsw3000c01v3In2FailTrap, hsw3000c01v3In1ExtFailTrap, hsw3000c01v3In2ExtFailTrap, hsw3000c01v3BlindExtFailTrap, hsw3000c01v3EqualPidTrap, 
				hsw3000c01v3SelOut1Trap, hsw3000c01v3SelOut2Trap, hsw3000c01v3EqualUmidTrap, hsw3000c01v3Gpi3StatTrap, hsw3000c01v3In1PhyFailTrap, 
				hsw3000c01v3In1FmtFailTrap, hsw3000c01v3In1IncFailTrap, hsw3000c01v3In1GpiFailTrap, hsw3000c01v3In1BlkFailTrap, hsw3000c01v3In1FrzFailTrap, 
				hsw3000c01v3In1PatFailTrap, hsw3000c01v3In1CrcFailTrap, hsw3000c01v3In1SilFailTrap, hsw3000c01v3In1OvrFailTrap, hsw3000c01v3In1PhFailTrap, 
				hsw3000c01v3In1PreFailTrap, hsw3000c01v3In2PhyFailTrap, hsw3000c01v3In2FmtFailTrap, hsw3000c01v3In2IncFailTrap, hsw3000c01v3In2GpiFailTrap, 
				hsw3000c01v3In2BlkFailTrap, hsw3000c01v3In2FrzFailTrap, hsw3000c01v3In2PatFailTrap, hsw3000c01v3In2CrcFailTrap, hsw3000c01v3In2SilFailTrap, 
				hsw3000c01v3In2OvrFailTrap, hsw3000c01v3In2PhFailTrap, hsw3000c01v3In2PreFailTrap, hsw3000c01v3RefFailTrap, hsw3000c01v3LockFailTrap, 
				hsw3000c01v3In1FormatTrap, hsw3000c01v3In2FormatTrap, hsw3000c01v3RefFormatTrap, hsw3000c01v3In1Grp1PresTrap, hsw3000c01v3In1Grp2PresTrap, 
				hsw3000c01v3In1Grp3PresTrap, hsw3000c01v3In1Grp4PresTrap, hsw3000c01v3In1Grp1P0StatTrap, hsw3000c01v3In1Grp1P1StatTrap, hsw3000c01v3In1Grp2P0StatTrap, 
				hsw3000c01v3In1Grp2P1StatTrap, hsw3000c01v3In1Grp3P0StatTrap, hsw3000c01v3In1Grp3P1StatTrap, hsw3000c01v3In1Grp4P0StatTrap, hsw3000c01v3In1Grp4P1StatTrap, 
				hsw3000c01v3In2Grp1PresTrap, hsw3000c01v3In2Grp2PresTrap, hsw3000c01v3In2Grp3PresTrap, hsw3000c01v3In2Grp4PresTrap, hsw3000c01v3In2Grp1P0StatTrap, 
				hsw3000c01v3In2Grp1P1StatTrap, hsw3000c01v3In2Grp2P0StatTrap, hsw3000c01v3In2Grp2P1StatTrap, hsw3000c01v3In2Grp3P0StatTrap, hsw3000c01v3In2Grp3P1StatTrap, 
				hsw3000c01v3In2Grp4P0StatTrap, hsw3000c01v3In2Grp4P1StatTrap, hsw3000c01v3In1WssStatTrap, hsw3000c01v3In1ViiStatTrap, hsw3000c01v3In12016StatTrap, 
				hsw3000c01v3In2WssStatTrap, hsw3000c01v3In2ViiStatTrap, hsw3000c01v3In22016StatTrap, hsw3000c01v3In1TxtLinLowTrap, hsw3000c01v3In2TxtLinLowTrap, 
				hsw3000c01v3In1WssCodTrap, hsw3000c01v3In1ViiAfdCodTrap, hsw3000c01v3In12016AfdCodTrap, hsw3000c01v3In2WssCodTrap, hsw3000c01v3In2ViiAfdCodTrap, 
				hsw3000c01v3In22016CodTrap }
			STATUS current
			DESCRIPTION
				"Module HSW3000C01V3 Trap Group"
			::= { trapGroup 364803 }

		-- 1.3.6.1.4.1.10106.2.3.2.371701
		eop0020c01v1TrapGroup NOTIFICATION-GROUP
		NOTIFICATIONS {eop0020c01v1NoSigATrap, eop0020c01v1UnlockATrap, eop0020c01v1LFailATrap, eop0020c01v1NoSigBTrap, eop0020c01v1UnlockBTrap, 
				eop0020c01v1LFailBTrap }
			STATUS current
			DESCRIPTION
				"Module EOP0020C01V1 Trap Group"
			::= { trapGroup 371701 }

		-- 1.3.6.1.4.1.10106.2.3.2.373501
		hop3147c01v1TrapGroup NOTIFICATION-GROUP
		NOTIFICATIONS {hop3147c01v1NoSignalTrap, hop3147c01v1UnlockTrap, hop3147c01v1EdhErrorTrap, hop3147c01v1TxtFailTrap, hop3147c01v1TxtInsFailTrap, 
				hop3147c01v1Gpi1Trap, hop3147c01v1Gpi2Trap, hop3147c01v1Gpi3Trap, hop3147c01v1Gpi4Trap, hop3147c01v1Gpi5Trap, 
				hop3147c01v1Gpi6Trap, hop3147c01v1Gpi7Trap, hop3147c01v1Gpi8Trap, hop3147c01v1Gpo1Trap, hop3147c01v1Gpo2Trap, 
				hop3147c01v1Gpo3Trap, hop3147c01v1Gpo4Trap, hop3147c01v1Gpo5Trap, hop3147c01v1Gpo6Trap, hop3147c01v1Gpo7Trap, 
				hop3147c01v1Gpo8Trap }
			STATUS current
			DESCRIPTION
				"Module HOP3147C01V1 Trap Group"
			::= { trapGroup 373501 }

		-- 1.3.6.1.4.1.10106.2.3.2.375001
		hvp3000c01v1TrapGroup NOTIFICATION-GROUP
		NOTIFICATIONS {hvp3000c01v1Output1Trap, hvp3000c01v1Output2Trap, hvp3000c01v1Output3Trap, hvp3000c01v1Output4Trap, hvp3000c01v1SyncFormatTrap, 
				hvp3000c01v1Out1LckStatTrap, hvp3000c01v1Out2LckStatTrap, hvp3000c01v1Out3LckStatTrap, hvp3000c01v1Out4LckStatTrap }
			STATUS current
			DESCRIPTION
				"Module HVP3000C01V1 Trap Group"
			::= { trapGroup 375001 }

		-- 1.3.6.1.4.1.10106.2.3.2.378901
		hdc3000c01v1TrapGroup NOTIFICATION-GROUP
		NOTIFICATIONS {hdc3000c01v1AnaRefFmtTrap, hdc3000c01v1ModeConvTrap, hdc3000c01v1OutAfdTrap, hdc3000c01v1OutCfTrap, hdc3000c01v1InAfdExpctTrap, 
				hdc3000c01v1InCfExpctTrap, hdc3000c01v1InAfdDetctTrap, hdc3000c01v1InCfDetctTrap, hdc3000c01v1InPhyFailTrap, hdc3000c01v1InFmtFailTrap, 
				hdc3000c01v1InIncFailTrap, hdc3000c01v1InCrcFailTrap, hdc3000c01v1PresAudG1FailTrap, hdc3000c01v1PresAudG2FailTrap, hdc3000c01v1PresAudG3FailTrap, 
				hdc3000c01v1PresAudG4FailTrap, hdc3000c01v1RefFailTrap, hdc3000c01v1RefFmtFailTrap, hdc3000c01v1LockFailTrap, hdc3000c01v1AudPair0FailTrap, 
				hdc3000c01v1AudPair1FailTrap, hdc3000c01v1AudPair2FailTrap, hdc3000c01v1AudPair3FailTrap, hdc3000c01v1AudPair4FailTrap, hdc3000c01v1AudPair5FailTrap, 
				hdc3000c01v1AudPair6FailTrap, hdc3000c01v1AudPair7FailTrap, hdc3000c01v1InFormatTrap, hdc3000c01v1RefFormatTrap }
			STATUS current
			DESCRIPTION
				"Module HDC3000C01V1 Trap Group"
			::= { trapGroup 378901 }

		-- 1.3.6.1.4.1.10106.2.3.2.379801
		hli3000c01v1TrapGroup NOTIFICATION-GROUP
		NOTIFICATIONS {hli3000c01v1PgmInsLogo1Trap, hli3000c01v1PgmInsLogo2Trap, hli3000c01v1PgmInsLogo3Trap, hli3000c01v1PgmInsLogo4Trap, hli3000c01v1SelLogo1Trap, 
				hli3000c01v1SelLogo2Trap, hli3000c01v1SelLogo3Trap, hli3000c01v1SelLogo4Trap, hli3000c01v1NoSignalTrap, hli3000c01v1UnlockTrap, 
				hli3000c01v1EdhErrorTrap, hli3000c01v1FormatTrap, hli3000c01v1Gpi1Trap, hli3000c01v1Gpi2Trap, hli3000c01v1Gpi3Trap, 
				hli3000c01v1Gpi4Trap, hli3000c01v1Gpi5Trap, hli3000c01v1Gpi6Trap, hli3000c01v1Gpi7Trap, hli3000c01v1Gpi8Trap }
			STATUS current
			DESCRIPTION
				"Module HLI3000C01V1 Trap Group"
			::= { trapGroup 379801 }

		-- 1.3.6.1.4.1.10106.2.3.2.379802
		hli3000c01v2TrapGroup NOTIFICATION-GROUP
		NOTIFICATIONS {hli3000c01v2ActivePresetTrap, hli3000c01v2PgmInsLogo1Trap, hli3000c01v2PgmInsLogo2Trap, hli3000c01v2PgmInsLogo3Trap, hli3000c01v2PgmInsLogo4Trap, 
				hli3000c01v2SelLogo1Trap, hli3000c01v2SelLogo2Trap, hli3000c01v2SelLogo3Trap, hli3000c01v2SelLogo4Trap, hli3000c01v2NoSignalTrap, 
				hli3000c01v2UnlockTrap, hli3000c01v2EdhErrorTrap, hli3000c01v2FormatTrap, hli3000c01v2Gpi1Trap, hli3000c01v2Gpi2Trap, 
				hli3000c01v2Gpi3Trap, hli3000c01v2Gpi4Trap, hli3000c01v2Gpi5Trap, hli3000c01v2Gpi6Trap, hli3000c01v2Gpi7Trap, 
				hli3000c01v2Gpi8Trap }
			STATUS current
			DESCRIPTION
				"Module HLI3000C01V2 Trap Group"
			::= { trapGroup 379802 }

		-- 1.3.6.1.4.1.10106.2.3.2.380001
		eop0010c01v1TrapGroup NOTIFICATION-GROUP
		NOTIFICATIONS {eop0010c01v1NoSigATrap, eop0010c01v1UnlockATrap, eop0010c01v1LFailATrap, eop0010c01v1NoSigBTrap, eop0010c01v1UnlockBTrap, 
				eop0010c01v1LFailBTrap }
			STATUS current
			DESCRIPTION
				"Module EOP0010C01V1 Trap Group"
			::= { trapGroup 380001 }

		-- 1.3.6.1.4.1.10106.2.3.2.382501
		hap3000c01v1TrapGroup NOTIFICATION-GROUP
		NOTIFICATIONS {hap3000c01v1NoSigTrap, hap3000c01v1UnlockTrap, hap3000c01v1EdhCrcTrap, hap3000c01v1NoRefTrap, hap3000c01v1RefUnlckTrap, 
				hap3000c01v1AudioFailTrap }
			STATUS current
			DESCRIPTION
				"Module HAP3000C01V1 Trap Group"
			::= { trapGroup 382501 }

		-- 1.3.6.1.4.1.10106.2.3.2.382502
		hap3000c01v2TrapGroup NOTIFICATION-GROUP
		NOTIFICATIONS {hap3000c01v2NoSigTrap, hap3000c01v2UnlockTrap, hap3000c01v2EdhCrcTrap, hap3000c01v2NoRefTrap, hap3000c01v2RefUnlckTrap, 
				hap3000c01v2AudioFailTrap }
			STATUS current
			DESCRIPTION
				"Module HAP3000C01V2 Trap Group"
			::= { trapGroup 382502 }

		-- 1.3.6.1.4.1.10106.2.3.2.386801
		psu3300c01v1TrapGroup NOTIFICATION-GROUP
		NOTIFICATIONS {psu3300c01v1PowerOffTrap, psu3300c01v1TempWarningTrap, psu3300c01v1TempFailTrap }
			STATUS current
			DESCRIPTION
				"Module PSU3300C01V1 Trap Group"
			::= { trapGroup 386801 }

		-- 1.3.6.1.4.1.10106.2.3.2.388901
		psu3300c02v1TrapGroup NOTIFICATION-GROUP
		NOTIFICATIONS {psu3300c02v1PowerOffTrap, psu3300c02v1TempWarningTrap, psu3300c02v1TempFailTrap }
			STATUS current
			DESCRIPTION
				"Module PSU3300C02V1 Trap Group"
			::= { trapGroup 388901 }

		-- 1.3.6.1.4.1.10106.2.3.2.389201
		psu3301c01v1TrapGroup NOTIFICATION-GROUP
		NOTIFICATIONS {psu3301c01v1PowerOffTrap, psu3301c01v1TempWarningTrap, psu3301c01v1TempFailTrap }
			STATUS current
			DESCRIPTION
				"Module PSU3301C01V1 Trap Group"
			::= { trapGroup 389201 }

		-- 1.3.6.1.4.1.10106.2.3.2.389501
		psu3301c03v1TrapGroup NOTIFICATION-GROUP
		NOTIFICATIONS {psu3301c03v1PowerOffTrap, psu3301c03v1TempWarningTrap, psu3301c03v1TempFailTrap }
			STATUS current
			DESCRIPTION
				"Module PSU3301C03V1 Trap Group"
			::= { trapGroup 389501 }

		-- 1.3.6.1.4.1.10106.2.3.2.392001
		avd3001c02v1TrapGroup NOTIFICATION-GROUP
		NOTIFICATIONS {avd3001c02v1NoSigATrap, avd3001c02v1UnlockATrap, avd3001c02v1SyncFormatTrap }
			STATUS current
			DESCRIPTION
				"Module AVD3001C02V1 Trap Group"
			::= { trapGroup 392001 }

		-- 1.3.6.1.4.1.10106.2.3.2.393601
		avd3001c01v1TrapGroup NOTIFICATION-GROUP
		NOTIFICATIONS {avd3001c01v1NoSigATrap, avd3001c01v1UnlockATrap, avd3001c01v1SyncFormatTrap }
			STATUS current
			DESCRIPTION
				"Module AVD3001C01V1 Trap Group"
			::= { trapGroup 393601 }

		-- 1.3.6.1.4.1.10106.2.3.2.393701
		avd3001c03v1TrapGroup NOTIFICATION-GROUP
		NOTIFICATIONS {avd3001c03v1NoSigATrap, avd3001c03v1UnlockATrap, avd3001c03v1SyncFormatTrap }
			STATUS current
			DESCRIPTION
				"Module AVD3001C03V1 Trap Group"
			::= { trapGroup 393701 }

		-- 1.3.6.1.4.1.10106.2.3.2.399601
		vgp3000c01v1TrapGroup NOTIFICATION-GROUP
		NOTIFICATIONS {vgp3000c01v1Gpi1Trap, vgp3000c01v1Gpi2Trap, vgp3000c01v1Gpi3Trap, vgp3000c01v1Gpi4Trap, vgp3000c01v1Gpi5Trap, 
				vgp3000c01v1Gpi6Trap, vgp3000c01v1Gpi7Trap, vgp3000c01v1Gpi8Trap, vgp3000c01v1Gpo1Trap, vgp3000c01v1Gpo2Trap, 
				vgp3000c01v1Gpo3Trap, vgp3000c01v1Gpo4Trap, vgp3000c01v1Gpo5Trap, vgp3000c01v1Gpo6Trap, vgp3000c01v1Gpo7Trap, 
				vgp3000c01v1Gpo8Trap }
			STATUS current
			DESCRIPTION
				"Module VGP3000C01V1 Trap Group"
			::= { trapGroup 399601 }

		-- 1.3.6.1.4.1.10106.2.3.2.403001
		ham3000c01v1TrapGroup NOTIFICATION-GROUP
		NOTIFICATIONS {ham3000c01v1NoSignalMainTrap, ham3000c01v1UnlockMainTrap, ham3000c01v1EdhErrorMainTrap, ham3000c01v1RefAbsentTrap, ham3000c01v1RefUnlockTrap, 
				ham3000c01v1Gr1MainPresTrap, ham3000c01v1Gr2MainPresTrap, ham3000c01v1Gr3MainPresTrap, ham3000c01v1Gr4MainPresTrap, ham3000c01v1AudStatMainTrap, 
				ham3000c01v1AudStatAuxTrap, ham3000c01v1AudStatAes1Trap, ham3000c01v1AudStatAes2Trap, ham3000c01v1OvldPgmOutTrap, ham3000c01v1OvldAes1OutTrap, 
				ham3000c01v1OvldAes2OutTrap, ham3000c01v1SilPgmOutTrap, ham3000c01v1SilAes1OutTrap, ham3000c01v1SilAes2OutTrap }
			STATUS current
			DESCRIPTION
				"Module HAM3000C01V1 Trap Group"
			::= { trapGroup 403001 }

		-- 1.3.6.1.4.1.10106.2.3.2.404701
		agw3000c01v1TrapGroup NOTIFICATION-GROUP
		NOTIFICATIONS {agw3000c01v1ModeTrap, agw3000c01v1DvbTModeTrap, agw3000c01v1AsiOut1InTrap, agw3000c01v1AsiOut2InTrap, agw3000c01v1IpOut1InTrap, 
				agw3000c01v1IpOut2InTrap, agw3000c01v1AsiIn1FailTrap, agw3000c01v1ExAsiIn1FailTrap, agw3000c01v1AsiIn2FailTrap, agw3000c01v1ExAsiIn2FailTrap, 
				agw3000c01v1IpIn1FailTrap, agw3000c01v1ExIpIn1FailTrap, agw3000c01v1IpIn2FailTrap, agw3000c01v1ExIpIn2FailTrap }
			STATUS current
			DESCRIPTION
				"Module AGW3000C01V1 Trap Group"
			::= { trapGroup 404701 }

		-- 1.3.6.1.4.1.10106.2.3.2.404702
		agw3000c01v2TrapGroup NOTIFICATION-GROUP
		NOTIFICATIONS {agw3000c01v2ModeTrap, agw3000c01v2DvbTModeTrap, agw3000c01v2AsiOut1InTrap, agw3000c01v2AsiOut2InTrap, agw3000c01v2IpOut1InTrap, 
				agw3000c01v2IpOut2InTrap, agw3000c01v2AsiIn1FailTrap, agw3000c01v2ExAsiIn1FailTrap, agw3000c01v2AsiIn2FailTrap, agw3000c01v2ExAsiIn2FailTrap, 
				agw3000c01v2IpIn1FailTrap, agw3000c01v2ExIpIn1FailTrap, agw3000c01v2IpIn2FailTrap, agw3000c01v2ExIpIn2FailTrap }
			STATUS current
			DESCRIPTION
				"Module AGW3000C01V2 Trap Group"
			::= { trapGroup 404702 }

		-- 1.3.6.1.4.1.10106.2.3.2.407601
		ham3000c02v1TrapGroup NOTIFICATION-GROUP
		NOTIFICATIONS {ham3000c02v1NoSignalMainTrap, ham3000c02v1UnlockMainTrap, ham3000c02v1EdhErrorMainTrap, ham3000c02v1RefAbsentTrap, ham3000c02v1RefUnlockTrap, 
				ham3000c02v1Gr1MainPresTrap, ham3000c02v1Gr2MainPresTrap, ham3000c02v1Gr3MainPresTrap, ham3000c02v1Gr4MainPresTrap, ham3000c02v1AudStatMainTrap, 
				ham3000c02v1AudStatAuxTrap, ham3000c02v1AudStatAes1Trap, ham3000c02v1AudStatAes2Trap, ham3000c02v1AudStatAnlg1Trap, ham3000c02v1AudStatAnlg2Trap, 
				ham3000c02v1OvldPgmOutTrap, ham3000c02v1OvldAes1OutTrap, ham3000c02v1OvldAes2OutTrap, ham3000c02v1SilPgmOutTrap, ham3000c02v1SilAes1OutTrap, 
				ham3000c02v1SilAes2OutTrap }
			STATUS current
			DESCRIPTION
				"Module HAM3000C02V1 Trap Group"
			::= { trapGroup 407601 }

		-- 1.3.6.1.4.1.10106.2.3.2.407701
		ham3000c03v1TrapGroup NOTIFICATION-GROUP
		NOTIFICATIONS {ham3000c03v1NoSignalMainTrap, ham3000c03v1UnlockMainTrap, ham3000c03v1EdhErrorMainTrap, ham3000c03v1RefAbsentTrap, ham3000c03v1RefUnlockTrap, 
				ham3000c03v1Gr1MainPresTrap, ham3000c03v1Gr2MainPresTrap, ham3000c03v1Gr3MainPresTrap, ham3000c03v1Gr4MainPresTrap, ham3000c03v1AudStatMainTrap, 
				ham3000c03v1AudStatAuxTrap, ham3000c03v1AudStatAes1Trap, ham3000c03v1AudStatAes2Trap, ham3000c03v1OvldPgmOutTrap, ham3000c03v1OvldAes1OutTrap, 
				ham3000c03v1OvldAes2OutTrap, ham3000c03v1OvldAnlg1OutTrap, ham3000c03v1OvldAnlg2OutTrap, ham3000c03v1SilPgmOutTrap, ham3000c03v1SilAes1OutTrap, 
				ham3000c03v1SilAes2OutTrap, ham3000c03v1SilAnlg1OutTrap, ham3000c03v1SilAnlg2OutTrap }
			STATUS current
			DESCRIPTION
				"Module HAM3000C03V1 Trap Group"
			::= { trapGroup 407701 }

		-- 1.3.6.1.4.1.10106.2.3.2.412201
		hop3147c02v1TrapGroup NOTIFICATION-GROUP
		NOTIFICATIONS {hop3147c02v1TxtFailTrap, hop3147c02v1TxtInsFailTrap, hop3147c02v1AudioFailTrap, hop3147c02v1AudioInsFailTrap, hop3147c02v1ViiInsFailTrap, 
				hop3147c02v1WssInsFailTrap, hop3147c02v1AfdInsFailTrap, hop3147c02v1NoSignal0Trap, hop3147c02v1Unlocked0Trap, hop3147c02v1EdhCrc0Trap, 
				hop3147c02v1NoSignal1Trap, hop3147c02v1Unlocked1Trap, hop3147c02v1EdhCrc1Trap, hop3147c02v1Gpi1Trap, hop3147c02v1Gpi2Trap, 
				hop3147c02v1Gpi3Trap, hop3147c02v1Gpi4Trap, hop3147c02v1Gpi5Trap, hop3147c02v1Gpi6Trap, hop3147c02v1Gpi7Trap, 
				hop3147c02v1Gpi8Trap, hop3147c02v1Gpo1Trap, hop3147c02v1Gpo2Trap, hop3147c02v1Gpo3Trap, hop3147c02v1Gpo4Trap, 
				hop3147c02v1Gpo5Trap, hop3147c02v1Gpo6Trap, hop3147c02v1Gpo7Trap, hop3147c02v1Gpo8Trap, hop3147c02v1VitcAtcPresTrap, 
				hop3147c02v1TxtAuxPresTrap, hop3147c02v1TxtPresTrap }
			STATUS current
			DESCRIPTION
				"Module HOP3147C02V1 Trap Group"
			::= { trapGroup 412201 }

		-- 1.3.6.1.4.1.10106.2.3.2.415501
		act3000c01v1TrapGroup NOTIFICATION-GROUP
		NOTIFICATIONS {act3000c01v1StateSelTrap, act3000c01v1SwitchModeTrap, act3000c01v1StatusIn1Trap, act3000c01v1StatusIn2Trap, act3000c01v1StatusIn1ExtTrap, 
				act3000c01v1StatusIn2ExtTrap, act3000c01v1StatusIn1ClipTrap, act3000c01v1StatusIn2ClipTrap, act3000c01v1SelOut1Trap, act3000c01v1SelOut2Trap, 
				act3000c01v1Gpi1StatTrap, act3000c01v1FailSil1lTrap, act3000c01v1FailOvld1lTrap, act3000c01v1FailClip1lTrap, act3000c01v1FailAnti1Trap, 
				act3000c01v1FailSil1rTrap, act3000c01v1FailOvld1rTrap, act3000c01v1FailClip1rTrap, act3000c01v1FailExt1Trap, act3000c01v1FailSil2lTrap, 
				act3000c01v1FailOvld2lTrap, act3000c01v1FailClip2lTrap, act3000c01v1FailAnti2Trap, act3000c01v1FailSil2rTrap, act3000c01v1FailOvld2rTrap, 
				act3000c01v1FailClip2rTrap, act3000c01v1FailExt2Trap }
			STATUS current
			DESCRIPTION
				"Module ACT3000C01V1 Trap Group"
			::= { trapGroup 415501 }

		-- 1.3.6.1.4.1.10106.2.3.2.416301
		hvd2000c01v1TrapGroup NOTIFICATION-GROUP
		NOTIFICATIONS {hvd2000c01v1NoSigTrap, hvd2000c01v1UnlockTrap }
			STATUS current
			DESCRIPTION
				"Module HVD2000C01V1 Trap Group"
			::= { trapGroup 416301 }

		-- 1.3.6.1.4.1.10106.2.3.2.422601
		tsa3000c01v1TrapGroup NOTIFICATION-GROUP
		NOTIFICATIONS {tsa3000c01v1ModeTrap, tsa3000c01v1SelectedInputTrap, tsa3000c01v1AsiIn1FailTrap, tsa3000c01v1ExAsiIn1FailTrap, tsa3000c01v1AsiIn2FailTrap, 
				tsa3000c01v1ExAsiIn2FailTrap, tsa3000c01v1IpIn1FailTrap, tsa3000c01v1ExIpIn1FailTrap, tsa3000c01v1IpIn2FailTrap, tsa3000c01v1ExIpIn2FailTrap, 
				tsa3000c01v1LinkTrap }
			STATUS current
			DESCRIPTION
				"Module TSA3000C01V1 Trap Group"
			::= { trapGroup 422601 }

		-- 1.3.6.1.4.1.10106.2.3.2.432201
		tle2001c01v1TrapGroup NOTIFICATION-GROUP
		NOTIFICATIONS {tle2001c01v1Gpi1Trap, tle2001c01v1Gpi2Trap, tle2001c01v1Gpi3Trap, tle2001c01v1Gpi4Trap, tle2001c01v1RedBoardTrap, 
				tle2001c01v1EthLinkTrap, tle2001c01v1EthRedActTrap }
			STATUS current
			DESCRIPTION
				"Module TLE2001C01V1 Trap Group"
			::= { trapGroup 432201 }

		-- 1.3.6.1.4.1.10106.2.3.2.436601
		psu2000c02v1TrapGroup NOTIFICATION-GROUP
		NOTIFICATIONS {psu2000c02v1PowerOffTrap, psu2000c02v1TempWarningTrap, psu2000c02v1TempFailTrap }
			STATUS current
			DESCRIPTION
				"Module PSU2000C02V1 Trap Group"
			::= { trapGroup 436601 }

		-- 1.3.6.1.4.1.10106.2.3.2.437801
		eop2000c01v1TrapGroup NOTIFICATION-GROUP
		NOTIFICATIONS {eop2000c01v1InputATrap, eop2000c01v1InputBTrap, eop2000c01v1UnlockATrap, eop2000c01v1LFailATrap, eop2000c01v1UnlockBTrap, 
				eop2000c01v1LFailBTrap, eop2000c01v1OpTxPresTrap, eop2000c01v1OpRxPresTrap }
			STATUS current
			DESCRIPTION
				"Module EOP2000C01V1 Trap Group"
			::= { trapGroup 437801 }

		-- 1.3.6.1.4.1.10106.2.3.2.438701
		avd2001c01v1TrapGroup NOTIFICATION-GROUP
		NOTIFICATIONS {avd2001c01v1NoSigATrap, avd2001c01v1UnlockATrap, avd2001c01v1SyncFormatTrap }
			STATUS current
			DESCRIPTION
				"Module AVD2001C01V1 Trap Group"
			::= { trapGroup 438701 }

		-- 1.3.6.1.4.1.10106.2.3.2.442301
		hdc2000c01v1TrapGroup NOTIFICATION-GROUP
		NOTIFICATIONS {hdc2000c01v1AnaRefFmtTrap, hdc2000c01v1ModeConvTrap, hdc2000c01v1OutAfdTrap, hdc2000c01v1OutCfTrap, hdc2000c01v1InAfdExpctTrap, 
				hdc2000c01v1InCfExpctTrap, hdc2000c01v1InAfdDetctTrap, hdc2000c01v1InCfDetctTrap, hdc2000c01v1InPhyFailTrap, hdc2000c01v1InFmtFailTrap, 
				hdc2000c01v1InIncFailTrap, hdc2000c01v1InCrcFailTrap, hdc2000c01v1PresAudG1FailTrap, hdc2000c01v1PresAudG2FailTrap, hdc2000c01v1PresAudG3FailTrap, 
				hdc2000c01v1PresAudG4FailTrap, hdc2000c01v1RefFailTrap, hdc2000c01v1RefFmtFailTrap, hdc2000c01v1LockFailTrap, hdc2000c01v1AudPair0FailTrap, 
				hdc2000c01v1AudPair1FailTrap, hdc2000c01v1AudPair2FailTrap, hdc2000c01v1AudPair3FailTrap, hdc2000c01v1AudPair4FailTrap, hdc2000c01v1AudPair5FailTrap, 
				hdc2000c01v1AudPair6FailTrap, hdc2000c01v1AudPair7FailTrap, hdc2000c01v1InFormatTrap, hdc2000c01v1RefFormatTrap }
			STATUS current
			DESCRIPTION
				"Module HDC2000C01V1 Trap Group"
			::= { trapGroup 442301 }

		-- 1.3.6.1.4.1.10106.2.3.2.442701
		gps3002c04v1TrapGroup NOTIFICATION-GROUP
		NOTIFICATIONS {gps3002c04v1RedundanceModeTrap, gps3002c04v1HoldoverStatTrap, gps3002c04v1MaintenanceFailTrap, gps3002c04v1OutputsMutedTrap, gps3002c04v11ppsDisableTrap, 
				gps3002c04v1AntenaStatTrap }
			STATUS current
			DESCRIPTION
				"Module GPS3002C04V1 Trap Group"
			::= { trapGroup 442701 }

		-- 1.3.6.1.4.1.10106.2.3.2.445101
		hdc2000c02v1TrapGroup NOTIFICATION-GROUP
		NOTIFICATIONS {hdc2000c02v1AnaRefFmtTrap, hdc2000c02v1ModeConvTrap, hdc2000c02v1OutAfdTrap, hdc2000c02v1OutCfTrap, hdc2000c02v1InAfdExpctTrap, 
				hdc2000c02v1InCfExpctTrap, hdc2000c02v1InAfdDetctTrap, hdc2000c02v1InCfDetctTrap, hdc2000c02v1InPhyFailTrap, hdc2000c02v1InFmtFailTrap, 
				hdc2000c02v1InIncFailTrap, hdc2000c02v1InCrcFailTrap, hdc2000c02v1PresAudG1FailTrap, hdc2000c02v1PresAudG2FailTrap, hdc2000c02v1PresAudG3FailTrap, 
				hdc2000c02v1PresAudG4FailTrap, hdc2000c02v1RefFailTrap, hdc2000c02v1RefFmtFailTrap, hdc2000c02v1LockFailTrap, hdc2000c02v1AudPair0FailTrap, 
				hdc2000c02v1AudPair1FailTrap, hdc2000c02v1AudPair2FailTrap, hdc2000c02v1AudPair3FailTrap, hdc2000c02v1AudPair4FailTrap, hdc2000c02v1AudPair5FailTrap, 
				hdc2000c02v1AudPair6FailTrap, hdc2000c02v1AudPair7FailTrap, hdc2000c02v1InFormatTrap, hdc2000c02v1RefFormatTrap }
			STATUS current
			DESCRIPTION
				"Module HDC2000C02V1 Trap Group"
			::= { trapGroup 445101 }

		-- 1.3.6.1.4.1.10106.2.3.2.446901
		hxc3000c01v1TrapGroup NOTIFICATION-GROUP
		NOTIFICATIONS {hxc3000c01v1AnaRefFmtTrap, hxc3000c01v1ModeConvTrap, hxc3000c01v1OutAfdTrap, hxc3000c01v1OutCfTrap, hxc3000c01v1InAfdExpctTrap, 
				hxc3000c01v1InCfExpctTrap, hxc3000c01v1TxFmtTrap, hxc3000c01v1DeintAlgorithmTrap, hxc3000c01v1InPhyFailTrap, hxc3000c01v1InFmtFailTrap, 
				hxc3000c01v1InIncFailTrap, hxc3000c01v1InCrcFailTrap, hxc3000c01v1PresAudG1FailTrap, hxc3000c01v1PresAudG2FailTrap, hxc3000c01v1PresAudG3FailTrap, 
				hxc3000c01v1PresAudG4FailTrap, hxc3000c01v1RefFailTrap, hxc3000c01v1RefFmtFailTrap, hxc3000c01v1LockFailTrap, hxc3000c01v1AudPair0FailTrap, 
				hxc3000c01v1AudPair1FailTrap, hxc3000c01v1AudPair2FailTrap, hxc3000c01v1AudPair3FailTrap, hxc3000c01v1AudPair4FailTrap, hxc3000c01v1AudPair5FailTrap, 
				hxc3000c01v1AudPair6FailTrap, hxc3000c01v1AudPair7FailTrap, hxc3000c01v1InAfdDetctTrap, hxc3000c01v1InCfDetctTrap, hxc3000c01v1InFormatTrap, 
				hxc3000c01v1RefFormatTrap, hxc3000c01v1TxFormatTrap }
			STATUS current
			DESCRIPTION
				"Module HXC3000C01V1 Trap Group"
			::= { trapGroup 446901 }

		-- 1.3.6.1.4.1.10106.2.3.2.454401
		hsw2000c01v1TrapGroup NOTIFICATION-GROUP
		NOTIFICATIONS {hsw2000c01v1StateSelTrap, hsw2000c01v1SwitchModeTrap, hsw2000c01v1BypassEnableTrap, hsw2000c01v1In1FailTrap, hsw2000c01v1In2FailTrap, 
				hsw2000c01v1EqualPidTrap, hsw2000c01v1SelOut1Trap, hsw2000c01v1SelOut2Trap, hsw2000c01v1EqualUmidTrap, hsw2000c01v1In1PhyFailTrap, 
				hsw2000c01v1In1FmtFailTrap, hsw2000c01v1In1IncFailTrap, hsw2000c01v1In1BlkFailTrap, hsw2000c01v1In1FrzFailTrap, hsw2000c01v1In1PatFailTrap, 
				hsw2000c01v1In1CrcFailTrap, hsw2000c01v1In1SilFailTrap, hsw2000c01v1In1OvrFailTrap, hsw2000c01v1In1PhFailTrap, hsw2000c01v1In1PreFailTrap, 
				hsw2000c01v1In2PhyFailTrap, hsw2000c01v1In2FmtFailTrap, hsw2000c01v1In2IncFailTrap, hsw2000c01v1In2BlkFailTrap, hsw2000c01v1In2FrzFailTrap, 
				hsw2000c01v1In2PatFailTrap, hsw2000c01v1In2CrcFailTrap, hsw2000c01v1In2SilFailTrap, hsw2000c01v1In2OvrFailTrap, hsw2000c01v1In2PhFailTrap, 
				hsw2000c01v1In2PreFailTrap, hsw2000c01v1RefFailTrap, hsw2000c01v1LockFailTrap, hsw2000c01v1In1FormatTrap, hsw2000c01v1In2FormatTrap, 
				hsw2000c01v1RefFormatTrap, hsw2000c01v1In1Grp1PresTrap, hsw2000c01v1In1Grp2PresTrap, hsw2000c01v1In1Grp3PresTrap, hsw2000c01v1In1Grp4PresTrap, 
				hsw2000c01v1In1Grp1P0StatTrap, hsw2000c01v1In1Grp1P1StatTrap, hsw2000c01v1In1Grp2P0StatTrap, hsw2000c01v1In1Grp2P1StatTrap, hsw2000c01v1In1Grp3P0StatTrap, 
				hsw2000c01v1In1Grp3P1StatTrap, hsw2000c01v1In1Grp4P0StatTrap, hsw2000c01v1In1Grp4P1StatTrap, hsw2000c01v1In2Grp1PresTrap, hsw2000c01v1In2Grp2PresTrap, 
				hsw2000c01v1In2Grp3PresTrap, hsw2000c01v1In2Grp4PresTrap, hsw2000c01v1In2Grp1P0StatTrap, hsw2000c01v1In2Grp1P1StatTrap, hsw2000c01v1In2Grp2P0StatTrap, 
				hsw2000c01v1In2Grp2P1StatTrap, hsw2000c01v1In2Grp3P0StatTrap, hsw2000c01v1In2Grp3P1StatTrap, hsw2000c01v1In2Grp4P0StatTrap, hsw2000c01v1In2Grp4P1StatTrap, 
				hsw2000c01v1In1WssCodTrap, hsw2000c01v1In1WssStatTrap, hsw2000c01v1In1ViiAfdCodTrap, hsw2000c01v1In1ViiStatTrap, hsw2000c01v1In12016AfdCodTrap, 
				hsw2000c01v1In12016StatTrap, hsw2000c01v1In2WssCodTrap, hsw2000c01v1In2WssStatTrap, hsw2000c01v1In2ViiAfdCodTrap, hsw2000c01v1In2ViiStatTrap, 
				hsw2000c01v1In22016CodTrap, hsw2000c01v1In22016StatTrap, hsw2000c01v1In1TxtLinLowTrap, hsw2000c01v1In2TxtLinLowTrap }
			STATUS current
			DESCRIPTION
				"Module HSW2000C01V1 Trap Group"
			::= { trapGroup 454401 }

		-- 1.3.6.1.4.1.10106.2.3.2.454501
		htg2000c01v1TrapGroup NOTIFICATION-GROUP
		NOTIFICATIONS {htg2000c01v1ExpRefFormatTrap, htg2000c01v1RefInputTrap, htg2000c01v1OutFormat1Trap, htg2000c01v1OutFormat2Trap, htg2000c01v1OutFormat3Trap, 
				htg2000c01v1ArefFailTrap, htg2000c01v1DrefFailTrap, htg2000c01v1IrefFailTrap, htg2000c01v1RefIncFailTrap, htg2000c01v1RefLockFailTrap, 
				htg2000c01v1DrefCrcFailTrap, htg2000c01v1ArefFormatTrap, htg2000c01v1DrefFormatTrap }
			STATUS current
			DESCRIPTION
				"Module HTG2000C01V1 Trap Group"
			::= { trapGroup 454501 }

		-- 1.3.6.1.4.1.10106.2.3.2.454502
		htg2000c01v2TrapGroup NOTIFICATION-GROUP
		NOTIFICATIONS {htg2000c01v2ExpRefFormatTrap, htg2000c01v2RefInputTrap, htg2000c01v2OutFormat1Trap, htg2000c01v2OutFormat2Trap, htg2000c01v2OutFormat3Trap, 
				htg2000c01v2ArefFailTrap, htg2000c01v2DrefFailTrap, htg2000c01v2IrefFailTrap, htg2000c01v2RefIncFailTrap, htg2000c01v2RefLockFailTrap, 
				htg2000c01v2DrefCrcFailTrap, htg2000c01v2ArefFormatTrap, htg2000c01v2DrefFormatTrap }
			STATUS current
			DESCRIPTION
				"Module HTG2000C01V2 Trap Group"
			::= { trapGroup 454502 }

		-- 1.3.6.1.4.1.10106.2.3.2.456201
		aad2000c01v1TrapGroup NOTIFICATION-GROUP
		NOTIFICATIONS {aad2000c01v1SilenceTrap, aad2000c01v1OverloadTrap }
			STATUS current
			DESCRIPTION
				"Module AAD2000C01V1 Trap Group"
			::= { trapGroup 456201 }

		-- 1.3.6.1.4.1.10106.2.3.2.460201
		aad2000c02v1TrapGroup NOTIFICATION-GROUP
		NOTIFICATIONS {aad2000c02v1SilenceTrap, aad2000c02v1OverloadTrap }
			STATUS current
			DESCRIPTION
				"Module AAD2000C02V1 Trap Group"
			::= { trapGroup 460201 }

		-- 1.3.6.1.4.1.10106.2.3.2.460301
		aad2000c03v1TrapGroup NOTIFICATION-GROUP
		NOTIFICATIONS {aad2000c03v1SilenceTrap, aad2000c03v1OverloadTrap }
			STATUS current
			DESCRIPTION
				"Module AAD2000C03V1 Trap Group"
			::= { trapGroup 460301 }

		-- 1.3.6.1.4.1.10106.2.3.2.460401
		aad2000c04v1TrapGroup NOTIFICATION-GROUP
		NOTIFICATIONS {aad2000c04v1SilenceTrap, aad2000c04v1OverloadTrap }
			STATUS current
			DESCRIPTION
				"Module AAD2000C04V1 Trap Group"
			::= { trapGroup 460401 }

		-- 1.3.6.1.4.1.10106.2.3.2.461001
		ipa2000c01v1TrapGroup NOTIFICATION-GROUP
		NOTIFICATIONS {ipa2000c01v1InputTrap, ipa2000c01v1SwModeTrap, ipa2000c01v1Ch1PriorTrap, ipa2000c01v1Ch2PriorTrap, ipa2000c01v1DvbTModeTrap, 
				ipa2000c01v1Ch1SelectionTrap, ipa2000c01v1Ch2SelectionTrap, ipa2000c01v1OutDelayTrap, ipa2000c01v1PacketDelayTrap, ipa2000c01v1Link1Trap, 
				ipa2000c01v1System1Trap, ipa2000c01v1Link2Trap, ipa2000c01v1System2Trap, ipa2000c01v11ppsFailTrap, ipa2000c01v113mhzFailTrap, 
				ipa2000c01v1OutputFailTrap, ipa2000c01v1SyncLossErr1Trap, ipa2000c01v1SyncByteErr1Trap, ipa2000c01v1PatError1Trap, ipa2000c01v1CcError1Trap, 
				ipa2000c01v1PmtError1Trap, ipa2000c01v1PidError1Trap, ipa2000c01v1MipError1Trap, ipa2000c01v1GlobalError1Trap, ipa2000c01v1SyncLossErr2Trap, 
				ipa2000c01v1SyncByteErr2Trap, ipa2000c01v1PatError2Trap, ipa2000c01v1CcError2Trap, ipa2000c01v1PmtError2Trap, ipa2000c01v1PidError2Trap, 
				ipa2000c01v1MipError2Trap, ipa2000c01v1GlobalError2Trap, ipa2000c01v1Ch1DelWarTrap, ipa2000c01v1Ch2DelWarTrap, ipa2000c01v1GlobalSeamTrap }
			STATUS current
			DESCRIPTION
				"Module IPA2000C01V1 Trap Group"
			::= { trapGroup 461001 }

		-- 1.3.6.1.4.1.10106.2.3.2.467901
		tle2001c02v1TrapGroup NOTIFICATION-GROUP
		NOTIFICATIONS {tle2001c02v1Gpi1Trap, tle2001c02v1Gpi2Trap, tle2001c02v1Gpi3Trap, tle2001c02v1Gpi4Trap, tle2001c02v1RedBoardTrap, 
				tle2001c02v1EthLinkTrap, tle2001c02v1EthRedActTrap }
			STATUS current
			DESCRIPTION
				"Module TLE2001C02V1 Trap Group"
			::= { trapGroup 467901 }

		-- 1.3.6.1.4.1.10106.2.3.2.469001
		ddf2008c01v1TrapGroup NOTIFICATION-GROUP
		NOTIFICATIONS {ddf2008c01v1BackplaneLockedTrap }
			STATUS current
			DESCRIPTION
				"Module DDF2008C01V1 Trap Group"
			::= { trapGroup 469001 }

		-- 1.3.6.1.4.1.10106.2.3.2.470001
		hfs2000c01v1TrapGroup NOTIFICATION-GROUP
		NOTIFICATIONS {hfs2000c01v1NoSigTrap, hfs2000c01v1UnlockTrap, hfs2000c01v1EdhCrcTrap, hfs2000c01v1NoRefTrap, hfs2000c01v1RefUnlockTrap }
			STATUS current
			DESCRIPTION
				"Module HFS2000C01V1 Trap Group"
			::= { trapGroup 470001 }

		-- 1.3.6.1.4.1.10106.2.3.2.471001
		htc3000c01v1TrapGroup NOTIFICATION-GROUP
		NOTIFICATIONS {htc3000c01v1RefAbsentTrap, htc3000c01v1RefUnlockTrap, htc3000c01v1NoSignalMainTrap, htc3000c01v1UnlockMainTrap, htc3000c01v1EdhErrorMainTrap, 
				htc3000c01v1NoSignalAuxTrap, htc3000c01v1UnlockAuxTrap, htc3000c01v1EdhErrorAuxTrap, htc3000c01v1IncompFmtTrap, htc3000c01v1TcFailTrap }
			STATUS current
			DESCRIPTION
				"Module HTC3000C01V1 Trap Group"
			::= { trapGroup 471001 }

		-- 1.3.6.1.4.1.10106.2.3.2.473501
		tle3001c02v1TrapGroup NOTIFICATION-GROUP
		NOTIFICATIONS {tle3001c02v1Gpi1Trap, tle3001c02v1Gpi2Trap, tle3001c02v1Gpi3Trap, tle3001c02v1Gpi4Trap, tle3001c02v1RedBoardTrap, 
				tle3001c02v1EthLinkTrap, tle3001c02v1EthRedActTrap }
			STATUS current
			DESCRIPTION
				"Module TLE3001C02V1 Trap Group"
			::= { trapGroup 473501 }

		-- 1.3.6.1.4.1.10106.2.3.2.474701
		adf2008c01v1TrapGroup NOTIFICATION-GROUP
		NOTIFICATIONS {adf2008c01v1BackplaneLockedTrap, adf2008c01v1AnalogInOverflTrap }
			STATUS current
			DESCRIPTION
				"Module ADF2008C01V1 Trap Group"
			::= { trapGroup 474701 }

		-- 1.3.6.1.4.1.10106.2.3.2.474801
		daf2008c01v1TrapGroup NOTIFICATION-GROUP
		NOTIFICATIONS {daf2008c01v1BackplaneLockedTrap }
			STATUS current
			DESCRIPTION
				"Module DAF2008C01V1 Trap Group"
			::= { trapGroup 474801 }

		-- 1.3.6.1.4.1.10106.2.3.2.478401
		tly3032c04v1TrapGroup NOTIFICATION-GROUP
		NOTIFICATIONS {tly3032c04v1Gpi1Trap, tly3032c04v1Gpi2Trap, tly3032c04v1Gpi3Trap, tly3032c04v1Gpi4Trap, tly3032c04v1Gpi5Trap, 
				tly3032c04v1Gpi6Trap, tly3032c04v1Gpi7Trap, tly3032c04v1Gpi8Trap, tly3032c04v1Gpi9Trap, tly3032c04v1Gpi10Trap, 
				tly3032c04v1Gpi11Trap, tly3032c04v1Gpi12Trap, tly3032c04v1Gpi13Trap, tly3032c04v1Gpi14Trap, tly3032c04v1Gpi15Trap, 
				tly3032c04v1Gpi16Trap, tly3032c04v1Gpi17Trap, tly3032c04v1Gpi18Trap, tly3032c04v1Gpi19Trap, tly3032c04v1Gpi20Trap, 
				tly3032c04v1Gpi21Trap, tly3032c04v1Gpi22Trap, tly3032c04v1Gpi23Trap, tly3032c04v1Gpi24Trap, tly3032c04v1Gpi25Trap, 
				tly3032c04v1Gpi26Trap, tly3032c04v1Gpi27Trap, tly3032c04v1Gpi28Trap, tly3032c04v1Gpi29Trap, tly3032c04v1Gpi30Trap, 
				tly3032c04v1Gpi31Trap, tly3032c04v1Gpi32Trap }
			STATUS current
			DESCRIPTION
				"Module TLY3032C04V1 Trap Group"
			::= { trapGroup 478401 }

		-- 1.3.6.1.4.1.10106.2.3.2.478901
		tle0001c02v1TrapGroup NOTIFICATION-GROUP
		NOTIFICATIONS {tle0001c02v1App1EnaTrap }
			STATUS current
			DESCRIPTION
				"Module TLE0001C02V1 Trap Group"
			::= { trapGroup 478901 }

		-- 1.3.6.1.4.1.10106.2.3.2.483501
		udp2000c01v1TrapGroup NOTIFICATION-GROUP
		NOTIFICATIONS {udp2000c01v1NoSignalTrap, udp2000c01v1UnlockTrap, udp2000c01v1DestAvailableTrap, udp2000c01v1PingStatusTrap, udp2000c01v1EmbedderFailTrap, 
				udp2000c01v1DeembedderFailTrap, udp2000c01v1EmbedderValidTrap, udp2000c01v1DeembedderValidTrap, udp2000c01v1VitcAtcPresTrap }
			STATUS current
			DESCRIPTION
				"Module UDP2000C01V1 Trap Group"
			::= { trapGroup 483501 }

		-- 1.3.6.1.4.1.10106.2.3.2.484901
		aem2008c01v1TrapGroup NOTIFICATION-GROUP
		NOTIFICATIONS {aem2008c01v1SdiInFailTrap, aem2008c01v1EdhInFailTrap, aem2008c01v1AudFailTrap, aem2008c01v1AudClipTrap }
			STATUS current
			DESCRIPTION
				"Module AEM2008C01V1 Trap Group"
			::= { trapGroup 484901 }

		-- 1.3.6.1.4.1.10106.2.3.2.485001
		ade2008c01v1TrapGroup NOTIFICATION-GROUP
		NOTIFICATIONS {ade2008c01v1SdiInFailTrap, ade2008c01v1EdhInFailTrap, ade2008c01v1AudFailTrap, ade2008c01v1AudClipTrap }
			STATUS current
			DESCRIPTION
				"Module ADE2008C01V1 Trap Group"
			::= { trapGroup 485001 }

		-- 1.3.6.1.4.1.10106.2.3.2.485901
		htg3001c01v1TrapGroup NOTIFICATION-GROUP
		NOTIFICATIONS {htg3001c01v1ExpRefFormatTrap, htg3001c01v1RefInputTrap, htg3001c01v1OutFormat1Trap, htg3001c01v1OutFormat2Trap, htg3001c01v1OutFormat3Trap, 
				htg3001c01v1ArefFailTrap, htg3001c01v1DrefFailTrap, htg3001c01v1IrefFailTrap, htg3001c01v1RefIncFailTrap, htg3001c01v1RefLockFailTrap, 
				htg3001c01v1DrefCrcFailTrap, htg3001c01v1ArefFormatTrap, htg3001c01v1DrefFormatTrap }
			STATUS current
			DESCRIPTION
				"Module HTG3001C01V1 Trap Group"
			::= { trapGroup 485901 }

		-- 1.3.6.1.4.1.10106.2.3.2.494401
		psu3300c03v1TrapGroup NOTIFICATION-GROUP
		NOTIFICATIONS {psu3300c03v1PowerOffTrap, psu3300c03v1TempWarningTrap, psu3300c03v1TempFailTrap }
			STATUS current
			DESCRIPTION
				"Module PSU3300C03V1 Trap Group"
			::= { trapGroup 494401 }

		-- 1.3.6.1.4.1.10106.2.3.2.496001
		ttd3000c03v1TrapGroup NOTIFICATION-GROUP
		NOTIFICATIONS {ttd3000c03v1ModeTrap, ttd3000c03v1InputATrap, ttd3000c03v1InputBTrap, ttd3000c03v1InputALvFailTrap, ttd3000c03v1InputAFrFailTrap, 
				ttd3000c03v1InputBLbFailTrap, ttd3000c03v1InputBFrFailTrap }
			STATUS current
			DESCRIPTION
				"Module TTD3000C03V1 Trap Group"
			::= { trapGroup 496001 }

		-- 1.3.6.1.4.1.10106.2.3.2.497501
		adb2008c01v1TrapGroup NOTIFICATION-GROUP
		NOTIFICATIONS {adb2008c01v1BusTimFailTrap, adb2008c01v1BusTimUnlckTrap, adb2008c01v1BusAudFailTrap, adb2008c01v1BusAudErrorTrap, adb2008c01v1AudClipErTrap, 
				adb2008c01v1AudInsFailTrap, adb2008c01v1AudOvldFailTrap }
			STATUS current
			DESCRIPTION
				"Module ADB2008C01V1 Trap Group"
			::= { trapGroup 497501 }

		-- 1.3.6.1.4.1.10106.2.3.2.497601
		dab2008c01v1TrapGroup NOTIFICATION-GROUP
		NOTIFICATIONS {dab2008c01v1BusSyncFailTrap, dab2008c01v1BusSyncUnlckTrap, dab2008c01v1BusAudFailTrap, dab2008c01v1BusAudErrorTrap, dab2008c01v1AudClipErTrap, 
				dab2008c01v1AudPresFailTrap, dab2008c01v1AudOvldFailTrap }
			STATUS current
			DESCRIPTION
				"Module DAB2008C01V1 Trap Group"
			::= { trapGroup 497601 }

		-- 1.3.6.1.4.1.10106.2.3.2.497701
		ddb2008c01v1TrapGroup NOTIFICATION-GROUP
		NOTIFICATIONS {ddb2008c01v1BusTimFailTrap, ddb2008c01v1BusTimUnlckTrap, ddb2008c01v1BusAudFailTrap, ddb2008c01v1BusAudErrorTrap, ddb2008c01v1AudClipErTrap, 
				ddb2008c01v1AudPresFailTrap, ddb2008c01v1AudInsFailTrap, ddb2008c01v1AudOvldErTrap }
			STATUS current
			DESCRIPTION
				"Module DDB2008C01V1 Trap Group"
			::= { trapGroup 497701 }

		-- 1.3.6.1.4.1.10106.2.3.2.514901
		smc2000c01v1TrapGroup NOTIFICATION-GROUP
		NOTIFICATIONS {smc2000c01v1SfpPresTrap, smc2000c01v1SfpFailTrap, smc2000c01v1SfpLosTrap, smc2000c01v1P1StatusTrap, smc2000c01v1P2StatusTrap, 
				smc2000c01v1PoStatusTrap }
			STATUS current
			DESCRIPTION
				"Module SMC2000C01V1 Trap Group"
			::= { trapGroup 514901 }

		-- 1.3.6.1.4.1.10106.2.3.2.517501
		gps2000c01v1TrapGroup NOTIFICATION-GROUP
		NOTIFICATIONS {gps2000c01v1GnssLosTrap, gps2000c01v1GnssPpsLosTrap, gps2000c01v1GnssUnlockTrap, gps2000c01v1GnssPpsErrTrap, gps2000c01v1PtpLosTrap, 
				gps2000c01v1PtpPpsLosTrap, gps2000c01v1PtpUnlockTrap, gps2000c01v1PtpPpsErrTrap, gps2000c01v1SyncStateTrap, gps2000c01v1ValidPpsTrap, 
				gps2000c01v1ModuleActiveTrap, gps2000c01v1RedSyncStateTrap, gps2000c01v1RedModuleTrap, gps2000c01v1FixModeTrap, gps2000c01v1PowerStatTrap, 
				gps2000c01v1AntennaStatTrap, gps2000c01v1EthLinkTrap, gps2000c01v1OnePpsStatTrap }
			STATUS current
			DESCRIPTION
				"Module GPS2000C01V1 Trap Group"
			::= { trapGroup 517501 }

		-- 1.3.6.1.4.1.10106.2.3.2.520301
		isw3000c01v1TrapGroup NOTIFICATION-GROUP
		NOTIFICATIONS {isw3000c01v1ModeTrap, isw3000c01v1DvbTModeTrap, isw3000c01v1InputTrap, isw3000c01v1OutDelayTrap, isw3000c01v1AsiMainPriorTrap, 
				isw3000c01v1AsiResPriorTrap, isw3000c01v1PacketDelayTrap, isw3000c01v1Ch1SelectionTrap, isw3000c01v1Ch2SelectionTrap, isw3000c01v1OutDelay0Trap, 
				isw3000c01v1OutDelay1Trap, isw3000c01v1DvbT2Lock1Trap, isw3000c01v1DvbT2Lock2Trap, isw3000c01v11ppsFailTrap, isw3000c01v110mhzFailTrap, 
				isw3000c01v1OutputFailTrap, isw3000c01v1Ts1DelWarTrap, isw3000c01v1Ts2DelWarTrap, isw3000c01v1ExtFail1Trap, isw3000c01v1ExtFail2Trap, 
				isw3000c01v1GlobalSeamTrap, isw3000c01v1SyncLossErr1Trap, isw3000c01v1SyncByteErr1Trap, isw3000c01v1PatError1Trap, isw3000c01v1CcError1Trap, 
				isw3000c01v1PmtError1Trap, isw3000c01v1PidError1Trap, isw3000c01v1MipError1Trap, isw3000c01v1GlobalError1Trap, isw3000c01v1SyncLossErr2Trap, 
				isw3000c01v1SyncByteErr2Trap, isw3000c01v1PatError2Trap, isw3000c01v1CcError2Trap, isw3000c01v1PmtError2Trap, isw3000c01v1PidError2Trap, 
				isw3000c01v1MipError2Trap, isw3000c01v1GlobalError2Trap, isw3000c01v1Ts1TraffFailTrap, isw3000c01v1Ts1NullPFailTrap, isw3000c01v1Ts2TraffFailTrap, 
				isw3000c01v1Ts2NullPFailTrap, isw3000c01v1OutDelayT2Trap }
			STATUS current
			DESCRIPTION
				"Module ISW3000C01V1 Trap Group"
			::= { trapGroup 520301 }

		-- 1.3.6.1.4.1.10106.2.3.2.520302
		isw3000c01v2TrapGroup NOTIFICATION-GROUP
		NOTIFICATIONS {isw3000c01v2ModeTrap, isw3000c01v2DvbTModeTrap, isw3000c01v2InputTrap, isw3000c01v2OutDelayTrap, isw3000c01v2AsiMainPriorTrap, 
				isw3000c01v2AsiResPriorTrap, isw3000c01v2OutDelayT2Trap, isw3000c01v2PacketDelayTrap, isw3000c01v2Ch1SelectionTrap, isw3000c01v2Ch2SelectionTrap, 
				isw3000c01v2OutDelay0Trap, isw3000c01v2OutDelay1Trap, isw3000c01v2DvbT2Lock1Trap, isw3000c01v2DvbT2Lock2Trap, isw3000c01v2Ts1TraffFailTrap, 
				isw3000c01v2Ts1NullPFailTrap, isw3000c01v2Ts2TraffFailTrap, isw3000c01v2Ts2NullPFailTrap, isw3000c01v21ppsFailTrap, isw3000c01v210mhzFailTrap, 
				isw3000c01v2OutputFailTrap, isw3000c01v2Ts1DelWarTrap, isw3000c01v2Ts2DelWarTrap, isw3000c01v2ExtFail1Trap, isw3000c01v2ExtFail2Trap, 
				isw3000c01v2GlobalSeamTrap, isw3000c01v2SyncLossErr1Trap, isw3000c01v2SyncByteErr1Trap, isw3000c01v2PatError1Trap, isw3000c01v2CcError1Trap, 
				isw3000c01v2PmtError1Trap, isw3000c01v2PidError1Trap, isw3000c01v2MipError1Trap, isw3000c01v2GlobalError1Trap, isw3000c01v2SyncLossErr2Trap, 
				isw3000c01v2SyncByteErr2Trap, isw3000c01v2PatError2Trap, isw3000c01v2CcError2Trap, isw3000c01v2PmtError2Trap, isw3000c01v2PidError2Trap, 
				isw3000c01v2MipError2Trap, isw3000c01v2GlobalError2Trap }
			STATUS current
			DESCRIPTION
				"Module ISW3000C01V2 Trap Group"
			::= { trapGroup 520302 }

		-- 1.3.6.1.4.1.10106.2.3.2.523601
		swc2000c01v1TrapGroup NOTIFICATION-GROUP
		NOTIFICATIONS {swc2000c01v1Gpi1Trap, swc2000c01v1Gpi2Trap, swc2000c01v1Gpi3Trap, swc2000c01v1Gpi4Trap, swc2000c01v1RedBoardTrap, 
				swc2000c01v1EthLinkTrap, swc2000c01v1EthRedActTrap }
			STATUS current
			DESCRIPTION
				"Module SWC2000C01V1 Trap Group"
			::= { trapGroup 523601 }

		-- 1.3.6.1.4.1.10106.2.3.2.524101
		psu2001c01v1TrapGroup NOTIFICATION-GROUP
		NOTIFICATIONS {psu2001c01v1PowerOffTrap, psu2001c01v1TempWarningTrap, psu2001c01v1TempFailTrap, psu2001c01v1PwrWarningTrap, psu2001c01v1PwrFailTrap }
			STATUS current
			DESCRIPTION
				"Module PSU2001C01V1 Trap Group"
			::= { trapGroup 524101 }

		-- 1.3.6.1.4.1.10106.2.3.2.527201
		eol2000c01v1TrapGroup NOTIFICATION-GROUP
		NOTIFICATIONS {eol2000c01v1InFormat1Trap, eol2000c01v1RefUnlockTrap, eol2000c01v1NoSigATrap, eol2000c01v1NoSigBTrap, eol2000c01v1SfpPresTrap }
			STATUS current
			DESCRIPTION
				"Module EOL2000C01V1 Trap Group"
			::= { trapGroup 527201 }

		-- 1.3.6.1.4.1.10106.2.3.2.529001
		ttd2000c01v1TrapGroup NOTIFICATION-GROUP
		NOTIFICATIONS {ttd2000c01v1FrInputTrap, ttd2000c01v1Onepps12Trap, ttd2000c01v1Onepps34Trap, ttd2000c01v1FrFailTrap, ttd2000c01v1ReTtlFailTrap, 
				ttd2000c01v1Re10mhzFailTrap }
			STATUS current
			DESCRIPTION
				"Module TTD2000C01V1 Trap Group"
			::= { trapGroup 529001 }

		-- 1.3.6.1.4.1.10106.2.3.2.530801
		psu2100c01v1TrapGroup NOTIFICATION-GROUP
		NOTIFICATIONS {psu2100c01v1PowerOffTrap, psu2100c01v1TempWarningTrap, psu2100c01v1TempFailTrap, psu2100c01v1PwrWarningTrap, psu2100c01v1PwrFailTrap }
			STATUS current
			DESCRIPTION
				"Module PSU2100C01V1 Trap Group"
			::= { trapGroup 530801 }

		-- 1.3.6.1.4.1.10106.2.3.2.538901
		atg2000c01v1TrapGroup NOTIFICATION-GROUP
		NOTIFICATIONS {atg2000c01v1RefLockFailTrap }
			STATUS current
			DESCRIPTION
				"Module ATG2000C01V1 Trap Group"
			::= { trapGroup 538901 }

		-- 1.3.6.1.4.1.10106.2.3.2.540801
		hvd2001c01v1TrapGroup NOTIFICATION-GROUP
		NOTIFICATIONS {hvd2001c01v1NoSigTrap, hvd2001c01v1UnlockTrap }
			STATUS current
			DESCRIPTION
				"Module HVD2001C01V1 Trap Group"
			::= { trapGroup 540801 }

		-- 1.3.6.1.4.1.10106.2.3.2.542501
		gti2000c01v1TrapGroup NOTIFICATION-GROUP
		NOTIFICATIONS {gti2000c01v1ModeTrap, gti2000c01v1InputTrap, gti2000c01v1RearFailTrap, gti2000c01v1FrontFailTrap, gti2000c01v1UnlockTrap }
			STATUS current
			DESCRIPTION
				"Module GTI2000C01V1 Trap Group"
			::= { trapGroup 542501 }

		-- 1.3.6.1.4.1.10106.2.3.2.552801
		tly2010c01v1TrapGroup NOTIFICATION-GROUP
		NOTIFICATIONS {tly2010c01v1GpoTrap, tly2010c01v1PhyGpoTrap }
			STATUS current
			DESCRIPTION
				"Module TLY2010C01V1 Trap Group"
			::= { trapGroup 552801 }

		-- 1.3.6.1.4.1.10106.2.3.2.553101
		hli2000c01v1TrapGroup NOTIFICATION-GROUP
		NOTIFICATIONS {hli2000c01v1RxFormatTrap, hli2000c01v1NoSignalTrap, hli2000c01v1EdhCrcTrap, hli2000c01v1LockFailTrap }
			STATUS current
			DESCRIPTION
				"Module HLI2000C01V1 Trap Group"
			::= { trapGroup 553101 }

		-- 1.3.6.1.4.1.10106.2.3.2.553901
		vct2000c01v1TrapGroup NOTIFICATION-GROUP
		NOTIFICATIONS {vct2000c01v1ModeTrap, vct2000c01v1InputTrap, vct2000c01v1InpMainFailTrap, vct2000c01v1GpiMainFailTrap, vct2000c01v1InpResFailTrap, 
				vct2000c01v1GpiResFailTrap }
			STATUS current
			DESCRIPTION
				"Module VCT2000C01V1 Trap Group"
			::= { trapGroup 553901 }

		-- 1.3.6.1.4.1.10106.2.3.2.554501
		hxc2000c01v1TrapGroup NOTIFICATION-GROUP
		NOTIFICATIONS {hxc2000c01v1AnaRefFmtTrap, hxc2000c01v1ModeConvTrap, hxc2000c01v1OutAfdTrap, hxc2000c01v1OutCfTrap, hxc2000c01v1InAfdExpctTrap, 
				hxc2000c01v1InCfExpctTrap, hxc2000c01v1TxFmtTrap, hxc2000c01v1DeintAlgorithmTrap, hxc2000c01v1InPhyFailTrap, hxc2000c01v1InFmtFailTrap, 
				hxc2000c01v1InIncFailTrap, hxc2000c01v1InCrcFailTrap, hxc2000c01v1PresAudG1FailTrap, hxc2000c01v1PresAudG2FailTrap, hxc2000c01v1PresAudG3FailTrap, 
				hxc2000c01v1PresAudG4FailTrap, hxc2000c01v1RefFailTrap, hxc2000c01v1RefFmtFailTrap, hxc2000c01v1LockFailTrap, hxc2000c01v1AudPair0FailTrap, 
				hxc2000c01v1AudPair1FailTrap, hxc2000c01v1AudPair2FailTrap, hxc2000c01v1AudPair3FailTrap, hxc2000c01v1AudPair4FailTrap, hxc2000c01v1AudPair5FailTrap, 
				hxc2000c01v1AudPair6FailTrap, hxc2000c01v1AudPair7FailTrap, hxc2000c01v1InAfdDetctTrap, hxc2000c01v1InCfDetctTrap, hxc2000c01v1InFormatTrap, 
				hxc2000c01v1RefFormatTrap, hxc2000c01v1TxFormatTrap }
			STATUS current
			DESCRIPTION
				"Module HXC2000C01V1 Trap Group"
			::= { trapGroup 554501 }

		-- 1.3.6.1.4.1.10106.2.3.2.555601
		uop2000c01v1TrapGroup NOTIFICATION-GROUP
		NOTIFICATIONS {uop2000c01v1InputATrap, uop2000c01v1InputBTrap, uop2000c01v1LosATrap, uop2000c01v1UnlockATrap, uop2000c01v1RateATrap, 
				uop2000c01v1LosBTrap, uop2000c01v1UnlockBTrap, uop2000c01v1RateBTrap }
			STATUS current
			DESCRIPTION
				"Module UOP2000C01V1 Trap Group"
			::= { trapGroup 555601 }

		-- 1.3.6.1.4.1.10106.2.3.2.574401
		act2000c01v1TrapGroup NOTIFICATION-GROUP
		NOTIFICATIONS {act2000c01v1ModeTrap, act2000c01v1InputTrap, act2000c01v1InpMainFailTrap, act2000c01v1GpiMainFailTrap, act2000c01v1InpResFailTrap, 
				act2000c01v1GpiResFailTrap }
			STATUS current
			DESCRIPTION
				"Module ACT2000C01V1 Trap Group"
			::= { trapGroup 574401 }

		-- 1.3.6.1.4.1.10106.2.3.2.577901
		utg2000c01v1TrapGroup NOTIFICATION-GROUP
		NOTIFICATIONS {utg2000c01v1ExpRefFormatTrap, utg2000c01v1RefInputTrap, utg2000c01v1ArefFailTrap, utg2000c01v1DrefFailTrap, utg2000c01v1IrefFailTrap, 
				utg2000c01v1RefIncFailTrap, utg2000c01v1RefLockFailTrap, utg2000c01v1DrefCrcFailTrap, utg2000c01v1ArefFormatTrap, utg2000c01v1DrefFormatTrap }
			STATUS current
			DESCRIPTION
				"Module UTG2000C01V1 Trap Group"
			::= { trapGroup 577901 }

		-- 1.3.6.1.4.1.10106.2.3.2.579101
		hvd2002c01v1TrapGroup NOTIFICATION-GROUP
		NOTIFICATIONS {hvd2002c01v1NoSigTrap, hvd2002c01v1UnlockTrap }
			STATUS current
			DESCRIPTION
				"Module HVD2002C01V1 Trap Group"
			::= { trapGroup 579101 }

		-- 1.3.6.1.4.1.10106.2.3.2.583701
		hfs2001c01v1TrapGroup NOTIFICATION-GROUP
		NOTIFICATIONS {hfs2001c01v1NoSigTrap, hfs2001c01v1UnlockTrap, hfs2001c01v1EdhCrcTrap, hfs2001c01v1NoRefTrap, hfs2001c01v1RefUnlockTrap }
			STATUS current
			DESCRIPTION
				"Module HFS2001C01V1 Trap Group"
			::= { trapGroup 583701 }

		-- 1.3.6.1.4.1.10106.2.3.2.586701
		gps3003c01v1TrapGroup NOTIFICATION-GROUP
		NOTIFICATIONS {gps3003c01v1GnssLosTrap, gps3003c01v1GnssPpsLosTrap, gps3003c01v1GnssUnlockTrap, gps3003c01v1GnssPpsErrTrap, gps3003c01v1PtpLosTrap, 
				gps3003c01v1PtpPpsLosTrap, gps3003c01v1PtpUnlockTrap, gps3003c01v1PtpPpsErrTrap, gps3003c01v1SyncStateTrap, gps3003c01v1ValidPpsTrap, 
				gps3003c01v1ModuleActiveTrap, gps3003c01v1RedSyncStateTrap, gps3003c01v1RedModuleTrap, gps3003c01v1FixModeTrap, gps3003c01v1PowerStatTrap, 
				gps3003c01v1AntennaStatTrap, gps3003c01v1EthLinkTrap, gps3003c01v1OnePpsStatTrap }
			STATUS current
			DESCRIPTION
				"Module GPS3003C01V1 Trap Group"
			::= { trapGroup 586701 }

		-- 1.3.6.1.4.1.10106.2.3.2.586801
		sem2000c01v1TrapGroup NOTIFICATION-GROUP
		NOTIFICATIONS {sem2000c01v1SfpPresTrap, sem2000c01v1SfpFailTrap, sem2000c01v1SfpLosTrap, sem2000c01v1P1StatusTrap, sem2000c01v1P2StatusTrap, 
				sem2000c01v1PoStatusTrap, sem2000c01v1BusUnlockTrap, sem2000c01v1BusLosTrap }
			STATUS current
			DESCRIPTION
				"Module SEM2000C01V1 Trap Group"
			::= { trapGroup 586801 }

		-- 1.3.6.1.4.1.10106.2.3.2.587301
		gps3003c02v1TrapGroup NOTIFICATION-GROUP
		NOTIFICATIONS {gps3003c02v1GnssLosTrap, gps3003c02v1GnssPpsLosTrap, gps3003c02v1GnssUnlockTrap, gps3003c02v1GnssPpsErrTrap, gps3003c02v1PtpLosTrap, 
				gps3003c02v1PtpPpsLosTrap, gps3003c02v1PtpUnlockTrap, gps3003c02v1PtpPpsErrTrap, gps3003c02v1SyncStateTrap, gps3003c02v1ValidPpsTrap, 
				gps3003c02v1ModuleActiveTrap, gps3003c02v1RedSyncStateTrap, gps3003c02v1RedModuleTrap, gps3003c02v1FixModeTrap, gps3003c02v1PowerStatTrap, 
				gps3003c02v1AntennaStatTrap, gps3003c02v1EthLinkTrap, gps3003c02v1OnePpsStatTrap }
			STATUS current
			DESCRIPTION
				"Module GPS3003C02V1 Trap Group"
			::= { trapGroup 587301 }

		-- 1.3.6.1.4.1.10106.2.3.2.587501
		gps3003c03v1TrapGroup NOTIFICATION-GROUP
		NOTIFICATIONS {gps3003c03v1GnssLosTrap, gps3003c03v1GnssPpsLosTrap, gps3003c03v1GnssUnlockTrap, gps3003c03v1GnssPpsErrTrap, gps3003c03v1PtpLosTrap, 
				gps3003c03v1PtpPpsLosTrap, gps3003c03v1PtpUnlockTrap, gps3003c03v1PtpPpsErrTrap, gps3003c03v1SyncStateTrap, gps3003c03v1ValidPpsTrap, 
				gps3003c03v1ModuleActiveTrap, gps3003c03v1RedSyncStateTrap, gps3003c03v1RedModuleTrap, gps3003c03v1FixModeTrap, gps3003c03v1PowerStatTrap, 
				gps3003c03v1AntennaStatTrap, gps3003c03v1EthLinkTrap, gps3003c03v1OnePpsStatTrap }
			STATUS current
			DESCRIPTION
				"Module GPS3003C03V1 Trap Group"
			::= { trapGroup 587501 }

		-- 1.3.6.1.4.1.10106.2.3.2.587701
		gps3003c04v1TrapGroup NOTIFICATION-GROUP
		NOTIFICATIONS {gps3003c04v1GnssLosTrap, gps3003c04v1GnssPpsLosTrap, gps3003c04v1GnssUnlockTrap, gps3003c04v1GnssPpsErrTrap, gps3003c04v1PtpLosTrap, 
				gps3003c04v1PtpPpsLosTrap, gps3003c04v1PtpUnlockTrap, gps3003c04v1PtpPpsErrTrap, gps3003c04v1SyncStateTrap, gps3003c04v1ValidPpsTrap, 
				gps3003c04v1ModuleActiveTrap, gps3003c04v1RedSyncStateTrap, gps3003c04v1RedModuleTrap, gps3003c04v1FixModeTrap, gps3003c04v1PowerStatTrap, 
				gps3003c04v1AntennaStatTrap, gps3003c04v1EthLinkTrap, gps3003c04v1OnePpsStatTrap }
			STATUS current
			DESCRIPTION
				"Module GPS3003C04V1 Trap Group"
			::= { trapGroup 587701 }

		-- 1.3.6.1.4.1.10106.2.3.2.592801
		ase2008c01v1TrapGroup NOTIFICATION-GROUP
		NOTIFICATIONS {ase2008c01v1AudChEn1Trap, ase2008c01v1AudChEn2Trap, ase2008c01v1AudChEn3Trap, ase2008c01v1AudChEn4Trap, ase2008c01v1AudChEn5Trap, 
				ase2008c01v1AudChEn6Trap, ase2008c01v1AudChEn7Trap, ase2008c01v1AudChEn8Trap, ase2008c01v1AudClipTrap }
			STATUS current
			DESCRIPTION
				"Module ASE2008C01V1 Trap Group"
			::= { trapGroup 592801 }

		-- 1.3.6.1.4.1.10106.2.3.2.592901
		aip2000c01v1TrapGroup NOTIFICATION-GROUP
		NOTIFICATIONS {aip2000c01v1StreamOk1Trap, aip2000c01v1BufferUnderf1Trap, aip2000c01v1BufferOverf1Trap, aip2000c01v1MalformedPck1Trap, aip2000c01v1StreamOk2Trap, 
				aip2000c01v1BufferUnderf2Trap, aip2000c01v1BufferOverf2Trap, aip2000c01v1MalformedPck2Trap, aip2000c01v1StreamOk3Trap, aip2000c01v1BufferUnderf3Trap, 
				aip2000c01v1BufferOverf3Trap, aip2000c01v1MalformedPck3Trap, aip2000c01v1StreamOk4Trap, aip2000c01v1BufferUnderf4Trap, aip2000c01v1BufferOverf4Trap, 
				aip2000c01v1MalformedPck4Trap, aip2000c01v1ShufOkTrap, aip2000c01v1Link1Trap, aip2000c01v1System1Trap, aip2000c01v1Link2Trap, 
				aip2000c01v1System2Trap, aip2000c01v1NoSignalTrap, aip2000c01v1UnlockTrap, aip2000c01v1FormatTrap, aip2000c01v1PtpStateTrap, 
				aip2000c01v1TxWorkinStat1Trap, aip2000c01v1ArpValid1Trap, aip2000c01v1IcmpError1Trap, aip2000c01v1TxWorkinStat2Trap, aip2000c01v1ArpValid2Trap, 
				aip2000c01v1IcmpError2Trap, aip2000c01v1TxWorkinStat3Trap, aip2000c01v1ArpValid3Trap, aip2000c01v1IcmpError3Trap, aip2000c01v1TxWorkinStat4Trap, 
				aip2000c01v1ArpValid4Trap, aip2000c01v1IcmpError4Trap, aip2000c01v1AsrcUnlocked1Trap, aip2000c01v1ProcessorStat1Trap, aip2000c01v1AsrcUnlocked2Trap, 
				aip2000c01v1ProcessorStat2Trap, aip2000c01v1Seamless0Trap, aip2000c01v1Seamless1Trap, aip2000c01v1ClkStatusTrap, aip2000c01v1Grp1PresTrap, 
				aip2000c01v1PresenciaMpxTrap, aip2000c01v1Grp2PresTrap, aip2000c01v1Grp3PresTrap, aip2000c01v1Grp4PresTrap }
			STATUS current
			DESCRIPTION
				"Module AIP2000C01V1 Trap Group"
			::= { trapGroup 592901 }

		-- 1.3.6.1.4.1.10106.2.3.2.593001
		asd2008c01v1TrapGroup NOTIFICATION-GROUP
		NOTIFICATIONS {asd2008c01v1SampFreqTrap, asd2008c01v1BitsPerSampTrap, asd2008c01v1AudClipTrap, asd2008c01v1TsLockTrap, asd2008c01v1PhaseLockTrap, 
				asd2008c01v1ChPres1Trap, asd2008c01v1ChPres2Trap, asd2008c01v1ChPres3Trap, asd2008c01v1ChPres4Trap, asd2008c01v1ChPres5Trap, 
				asd2008c01v1ChPres6Trap, asd2008c01v1ChPres7Trap, asd2008c01v1ChPres8Trap }
			STATUS current
			DESCRIPTION
				"Module ASD2008C01V1 Trap Group"
			::= { trapGroup 593001 }

		-- 1.3.6.1.4.1.10106.2.3.2.599301
		ded2008c01v1TrapGroup NOTIFICATION-GROUP
		NOTIFICATIONS {ded2008c01v1SdiInFailTrap, ded2008c01v1SdiG1FailTrap, ded2008c01v1SdiG2FailTrap, ded2008c01v1SdiG3FailTrap, ded2008c01v1SdiG4FailTrap, 
				ded2008c01v1Ref27mFailTrap, ded2008c01v1AudioProcFailTrap, ded2008c01v1In1AudFailTrap, ded2008c01v1In1RefFailTrap, ded2008c01v1In2AudFailTrap, 
				ded2008c01v1In2RefFailTrap, ded2008c01v1In3AudFailTrap, ded2008c01v1In3RefFailTrap, ded2008c01v1In4AudFailTrap, ded2008c01v1In4RefFailTrap, 
				ded2008c01v1In5AudFailTrap, ded2008c01v1In6AudFailTrap, ded2008c01v1In7AudFailTrap, ded2008c01v1In8AudFailTrap }
			STATUS current
			DESCRIPTION
				"Module DED2008C01V1 Trap Group"
			::= { trapGroup 599301 }

		-- 1.3.6.1.4.1.10106.2.3.2.600801
		uvd2000c01v1TrapGroup NOTIFICATION-GROUP
		NOTIFICATIONS {uvd2000c01v1InputTrap, uvd2000c01v1LosTrap, uvd2000c01v1UnlockTrap, uvd2000c01v1RateTrap }
			STATUS current
			DESCRIPTION
				"Module UVD2000C01V1 Trap Group"
			::= { trapGroup 600801 }

		-- 1.3.6.1.4.1.10106.2.3.2.607801
		deb2008c01v1TrapGroup NOTIFICATION-GROUP
		NOTIFICATIONS {deb2008c01v1AudClipErTrap, deb2008c01v1AudPresFailTrap, deb2008c01v1AudInsFailTrap, deb2008c01v1AudOvldErTrap }
			STATUS current
			DESCRIPTION
				"Module DEB2008C01V1 Trap Group"
			::= { trapGroup 607801 }

		-- 1.3.6.1.4.1.10106.2.3.2.607901
		def2008c01v1TrapGroup NOTIFICATION-GROUP
		NOTIFICATIONS {def2008c01v1AesIn1PresTrap, def2008c01v1Aes1RefPresTrap, def2008c01v1AesIn2PresTrap, def2008c01v1Aes2RefPresTrap, def2008c01v1AesIn3PresTrap, 
				def2008c01v1Aes3RefPresTrap, def2008c01v1AesIn4PresTrap, def2008c01v1Aes4RefPresTrap, def2008c01v1AesIn5PresTrap, def2008c01v1AesIn6PresTrap, 
				def2008c01v1AesIn7PresTrap, def2008c01v1AesIn8PresTrap, def2008c01v1BackplaneLockedTrap }
			STATUS current
			DESCRIPTION
				"Module DEF2008C01V1 Trap Group"
			::= { trapGroup 607901 }

		-- 1.3.6.1.4.1.10106.2.3.2.609201
		dad2000c01v1TrapGroup NOTIFICATION-GROUP
		NOTIFICATIONS {dad2000c01v1SigFailTrap, dad2000c01v1SigLowTrap }
			STATUS current
			DESCRIPTION
				"Module DAD2000C01V1 Trap Group"
			::= { trapGroup 609201 }

		-- 1.3.6.1.4.1.10106.2.3.2.616301
		gpd2000c01v1TrapGroup NOTIFICATION-GROUP
		NOTIFICATIONS {gpd2000c01v1VccGnss1FailTrap, gpd2000c01v1VccGnss2FailTrap, gpd2000c01v1VccGnss3FailTrap, gpd2000c01v1VccGnss4FailTrap, gpd2000c01v1VccAntennaFailTrap, 
				gpd2000c01v1IccAntennaFailTrap, gpd2000c01v1NoAntennaTrap }
			STATUS current
			DESCRIPTION
				"Module GPD2000C01V1 Trap Group"
			::= { trapGroup 616301 }

		-- 1.3.6.1.4.1.10106.2.3.2.620401
		hxc2000c02v1TrapGroup NOTIFICATION-GROUP
		NOTIFICATIONS {hxc2000c02v1AnaRefFmtTrap, hxc2000c02v1ModeConvTrap, hxc2000c02v1OutAfdTrap, hxc2000c02v1OutCfTrap, hxc2000c02v1InAfdExpctTrap, 
				hxc2000c02v1InCfExpctTrap, hxc2000c02v1TxFmtTrap, hxc2000c02v1DeintAlgorithmTrap, hxc2000c02v1InPhyFailTrap, hxc2000c02v1InFmtFailTrap, 
				hxc2000c02v1InIncFailTrap, hxc2000c02v1InCrcFailTrap, hxc2000c02v1PresAudG1FailTrap, hxc2000c02v1PresAudG2FailTrap, hxc2000c02v1PresAudG3FailTrap, 
				hxc2000c02v1PresAudG4FailTrap, hxc2000c02v1RefFailTrap, hxc2000c02v1RefFmtFailTrap, hxc2000c02v1LockFailTrap, hxc2000c02v1UxcPresTrap, 
				hxc2000c02v1AudPair0FailTrap, hxc2000c02v1AudPair1FailTrap, hxc2000c02v1AudPair2FailTrap, hxc2000c02v1AudPair3FailTrap, hxc2000c02v1AudPair4FailTrap, 
				hxc2000c02v1AudPair5FailTrap, hxc2000c02v1AudPair6FailTrap, hxc2000c02v1AudPair7FailTrap, hxc2000c02v1InAfdDetctTrap, hxc2000c02v1InCfDetctTrap, 
				hxc2000c02v1InFormatTrap, hxc2000c02v1RefFormatTrap, hxc2000c02v1TxFormatTrap }
			STATUS current
			DESCRIPTION
				"Module HXC2000C02V1 Trap Group"
			::= { trapGroup 620401 }

		-- 1.3.6.1.4.1.10106.2.3.2.623301
		mpx2000c01v1TrapGroup NOTIFICATION-GROUP
		NOTIFICATIONS {mpx2000c01v1AudioMpxNTrap, mpx2000c01v1ControlTrap, mpx2000c01v1MpxFailTrap, mpx2000c01v1AudFailTrap, mpx2000c01v1GpiTrap }
			STATUS current
			DESCRIPTION
				"Module MPX2000C01V1 Trap Group"
			::= { trapGroup 623301 }

		-- 1.3.6.1.4.1.10106.2.3.2.627101
		rfa2018c01v1TrapGroup NOTIFICATION-GROUP
		NOTIFICATIONS {rfa2018c01v1VoltFailTrap, rfa2018c01v1CurrFailTrap, rfa2018c01v1TempFailTrap }
			STATUS current
			DESCRIPTION
				"Module RFA2018C01V1 Trap Group"
			::= { trapGroup 627101 }

		
--  1.3.6.1.4.1.10106.3
		-- 1.3.6.1.4.1.10106.3
		albalaProducts OBJECT-IDENTITY
			STATUS current
			DESCRIPTION 
				"Managed information per product, sorted by code"
			::= { albalaRoot 3 }

		
--  This one is not a real product, but contains the settings for the agent polling behaviour.
-- 1.3.6.1.4.1.10106.3.2
		-- 1.3.6.1.4.1.10106.3.1
		chasis OBJECT IDENTIFIER ::= { albalaProducts 1 }

		
--  1.3.6.1.4.1.10106.3.2.2
		-- 1.3.6.1.4.1.10106.3.1.1
		moduleTable OBJECT-TYPE
			SYNTAX SEQUENCE OF ModuleEntry
			MAX-ACCESS not-accessible
			STATUS current
			DESCRIPTION
				"Table of managed modules"
			::= { chasis 1 }

		
--  1.3.6.1.4.1.10106.3.2.2.1
		-- 1.3.6.1.4.1.10106.3.1.1.1
		moduleEntry OBJECT-TYPE
			SYNTAX ModuleEntry
			MAX-ACCESS not-accessible
			STATUS current
			DESCRIPTION
				"Managed module data"
			INDEX { moduleIndex }
			::= { moduleTable 1 }

		
		ModuleEntry ::=
			SEQUENCE { 
				moduleIndex
					ModuleIndex,
				moduleTrapEnable
					AlarmEnable,
				moduleExpectedType
					ModuleType,
				moduleFoundType
					ModuleType,
				moduleStatus
					ModuleStatus
			 }

--  1.3.6.1.4.1.10106.3.2.2.1.1
		-- 1.3.6.1.4.1.10106.3.1.1.1.1
		moduleIndex OBJECT-TYPE
			SYNTAX ModuleIndex
			MAX-ACCESS accessible-for-notify
			STATUS current
			DESCRIPTION
				"Module position within frame"
			::= { moduleEntry 1 }

		
--  1.3.6.1.4.1.10106.3.2.2.1.9
		-- 1.3.6.1.4.1.10106.3.1.1.1.2
		moduleTrapEnable OBJECT-TYPE
			SYNTAX AlarmEnable
			MAX-ACCESS read-write
			STATUS current
			DESCRIPTION
				"Module presence and manageability events trap enable"
			::= { moduleEntry 2 }

		
--  1.3.6.1.4.1.10106.3.2.2.1.2
		-- 1.3.6.1.4.1.10106.3.1.1.1.3
		moduleExpectedType OBJECT-TYPE
			SYNTAX ModuleType
			MAX-ACCESS read-only
			STATUS current
			DESCRIPTION
				"Expected type of module. 'none' allows any kind of module to be managed in a generic way."
			::= { moduleEntry 3 }

		
--  1.3.6.1.4.1.10106.3.2.2.1.3
		-- 1.3.6.1.4.1.10106.3.1.1.1.4
		moduleFoundType OBJECT-TYPE
			SYNTAX ModuleType
			MAX-ACCESS read-only
			STATUS current
			DESCRIPTION
				"Type of module actually installed, if known by the agent."
			::= { moduleEntry 4 }

		
--  1.3.6.1.4.1.10106.3.2.2.1.7
		-- 1.3.6.1.4.1.10106.3.1.1.1.5
		moduleStatus OBJECT-TYPE
			SYNTAX ModuleStatus
			MAX-ACCESS read-only
			STATUS current
			DESCRIPTION
				"Module presence and manageability"
			::= { moduleEntry 5 }


		-- 1.3.6.1.4.1.10106.3.89101
		dvp3222p01v1 OBJECT IDENTIFIER ::= { albalaProducts 89101 }

		-- 1.3.6.1.4.1.10106.3.89101.1
		dvp3222p01v1Table  OBJECT-TYPE
			SYNTAX SEQUENCE OF Dvp3222p01v1Entry
			MAX-ACCESS not-accessible
			STATUS current
			DESCRIPTION
				"Module  DVP3222P01V1 Table"
			::= { dvp3222p01v1 1 }

		-- 1.3.6.1.4.1.10106.3.89101.1.1
		dvp3222p01v1Entry  OBJECT-TYPE
			SYNTAX Dvp3222p01v1Entry
			MAX-ACCESS not-accessible
			STATUS current
			DESCRIPTION
				"Module DVP3222P01V1 Entry"
			INDEX { dvp3222p01v1Index }
			::= { dvp3222p01v1Table 1 }

			Dvp3222p01v1Entry ::=
			SEQUENCE {
				dvp3222p01v1Index
				ModuleIndex,
				dvp3222p01v1Output1
				Inputs132,
				dvp3222p01v1Output2
				Inputs132,
				dvp3222p01v1SwitchTime
				PreselSwTime2,
				dvp3222p01v1NoSync
				BitFail,
				dvp3222p01v1SyncLines
				Bit06251525
			 }

		-- 1.3.6.1.4.1.10106.3.101291.1.1.1
		dvp3222p01v1Index OBJECT-TYPE
			SYNTAX ModuleIndex
			MAX-ACCESS read-only
			STATUS current
			DESCRIPTION
				"Index of DVP3222P01V1 Table"
		::= { dvp3222p01v1Entry 1 }

		-- 1.3.6.1.4.1.10106.3.101291.1.1.3
		dvp3222p01v1Output1 OBJECT-TYPE
			SYNTAX Inputs132
			MAX-ACCESS read-write
			STATUS current
			DESCRIPTION
				"Input routed to output 1"
		::= { dvp3222p01v1Entry 3 }

		-- 1.3.6.1.4.1.10106.3.101291.1.1.5
		dvp3222p01v1Output2 OBJECT-TYPE
			SYNTAX Inputs132
			MAX-ACCESS read-write
			STATUS current
			DESCRIPTION
				"Input routed to output 2"
		::= { dvp3222p01v1Entry 5 }

		-- 1.3.6.1.4.1.10106.3.101291.1.1.7
		dvp3222p01v1SwitchTime OBJECT-TYPE
			SYNTAX PreselSwTime2
			MAX-ACCESS read-write
			STATUS current
			DESCRIPTION
				"Allows selection of switching time"
		::= { dvp3222p01v1Entry 7 }

		-- 1.3.6.1.4.1.10106.3.101291.1.1.9
		dvp3222p01v1NoSync OBJECT-TYPE
			SYNTAX BitFail
			MAX-ACCESS read-only
			STATUS current
			DESCRIPTION
				"Sync presence status"
		::= { dvp3222p01v1Entry 9 }

		-- 1.3.6.1.4.1.10106.3.101291.1.1.11
		dvp3222p01v1SyncLines OBJECT-TYPE
			SYNTAX Bit06251525
			MAX-ACCESS read-only
			STATUS current
			DESCRIPTION
				"Number of lines of sync signal"
		::= { dvp3222p01v1Entry 11 }

		-- 1.3.6.1.4.1.10106.3.125101
		vct3000p01v1 OBJECT IDENTIFIER ::= { albalaProducts 125101 }

		-- 1.3.6.1.4.1.10106.3.125101.1
		vct3000p01v1Table  OBJECT-TYPE
			SYNTAX SEQUENCE OF Vct3000p01v1Entry
			MAX-ACCESS not-accessible
			STATUS current
			DESCRIPTION
				"Module  VCT3000P01V1 Table"
			::= { vct3000p01v1 1 }

		-- 1.3.6.1.4.1.10106.3.125101.1.1
		vct3000p01v1Entry  OBJECT-TYPE
			SYNTAX Vct3000p01v1Entry
			MAX-ACCESS not-accessible
			STATUS current
			DESCRIPTION
				"Module VCT3000P01V1 Entry"
			INDEX { vct3000p01v1Index }
			::= { vct3000p01v1Table 1 }

			Vct3000p01v1Entry ::=
			SEQUENCE {
				vct3000p01v1Index
				ModuleIndex,
				vct3000p01v1Mode
				ChgOverMode1,
				vct3000p01v1ModeTrapEnable
				AlarmEnable,
				vct3000p01v1Input
				ChgOverInput1,
				vct3000p01v1InputTrapEnable
				AlarmEnable,
				vct3000p01v1Gpi0
				Bit0Ina1Act,
				vct3000p01v1Gpi1
				Bit0Ina1Act,
				vct3000p01v1MainFail
				BitFail,
				vct3000p01v1MainFailTrapEnable
				AlarmEnable,
				vct3000p01v1ResFail
				BitFail,
				vct3000p01v1ResFailTrapEnable
				AlarmEnable
			 }

		-- 1.3.6.1.4.1.10106.3.101291.1.1.1
		vct3000p01v1Index OBJECT-TYPE
			SYNTAX ModuleIndex
			MAX-ACCESS read-only
			STATUS current
			DESCRIPTION
				"Index of VCT3000P01V1 Table"
		::= { vct3000p01v1Entry 1 }

		-- 1.3.6.1.4.1.10106.3.101291.1.1.3
		vct3000p01v1Mode OBJECT-TYPE
			SYNTAX ChgOverMode1
			MAX-ACCESS read-write
			STATUS current
			DESCRIPTION
				"Allows selecting the switching mode"
		::= { vct3000p01v1Entry 3 }

		-- 1.3.6.1.4.1.10106.3.101291.1.1.4
		vct3000p01v1ModeTrapEnable OBJECT-TYPE
			SYNTAX AlarmEnable
			MAX-ACCESS read-write
			STATUS current
			DESCRIPTION
				"Allows selecting the switching mode Trap Enable"
		::= { vct3000p01v1Entry 4 }

		-- 1.3.6.1.4.1.10106.3.101291.1.1.5
		vct3000p01v1Input OBJECT-TYPE
			SYNTAX ChgOverInput1
			MAX-ACCESS read-write
			STATUS current
			DESCRIPTION
				"Selected input"
		::= { vct3000p01v1Entry 5 }

		-- 1.3.6.1.4.1.10106.3.101291.1.1.6
		vct3000p01v1InputTrapEnable OBJECT-TYPE
			SYNTAX AlarmEnable
			MAX-ACCESS read-write
			STATUS current
			DESCRIPTION
				"Selected input Trap Enable"
		::= { vct3000p01v1Entry 6 }

		-- 1.3.6.1.4.1.10106.3.101291.1.1.7
		vct3000p01v1Gpi0 OBJECT-TYPE
			SYNTAX Bit0Ina1Act
			MAX-ACCESS read-only
			STATUS current
			DESCRIPTION
				"GPI0 input status"
		::= { vct3000p01v1Entry 7 }

		-- 1.3.6.1.4.1.10106.3.101291.1.1.9
		vct3000p01v1Gpi1 OBJECT-TYPE
			SYNTAX Bit0Ina1Act
			MAX-ACCESS read-only
			STATUS current
			DESCRIPTION
				"GPI1 input status"
		::= { vct3000p01v1Entry 9 }

		-- 1.3.6.1.4.1.10106.3.101291.1.1.11
		vct3000p01v1MainFail OBJECT-TYPE
			SYNTAX BitFail
			MAX-ACCESS read-only
			STATUS current
			DESCRIPTION
				"Main input status"
		::= { vct3000p01v1Entry 11 }

		-- 1.3.6.1.4.1.10106.3.101291.1.1.12
		vct3000p01v1MainFailTrapEnable OBJECT-TYPE
			SYNTAX AlarmEnable
			MAX-ACCESS read-write
			STATUS current
			DESCRIPTION
				"Main input status Trap Enable"
		::= { vct3000p01v1Entry 12 }

		-- 1.3.6.1.4.1.10106.3.101291.1.1.13
		vct3000p01v1ResFail OBJECT-TYPE
			SYNTAX BitFail
			MAX-ACCESS read-only
			STATUS current
			DESCRIPTION
				"Reserve input status"
		::= { vct3000p01v1Entry 13 }

		-- 1.3.6.1.4.1.10106.3.101291.1.1.14
		vct3000p01v1ResFailTrapEnable OBJECT-TYPE
			SYNTAX AlarmEnable
			MAX-ACCESS read-write
			STATUS current
			DESCRIPTION
				"Reserve input status Trap Enable"
		::= { vct3000p01v1Entry 14 }

		-- 1.3.6.1.4.1.10106.3.126001
		vct3000c02v1 OBJECT IDENTIFIER ::= { albalaProducts 126001 }

		-- 1.3.6.1.4.1.10106.3.126001.1
		vct3000c02v1Table  OBJECT-TYPE
			SYNTAX SEQUENCE OF Vct3000c02v1Entry
			MAX-ACCESS not-accessible
			STATUS current
			DESCRIPTION
				"Module  VCT3000C02V1 Table"
			::= { vct3000c02v1 1 }

		-- 1.3.6.1.4.1.10106.3.126001.1.1
		vct3000c02v1Entry  OBJECT-TYPE
			SYNTAX Vct3000c02v1Entry
			MAX-ACCESS not-accessible
			STATUS current
			DESCRIPTION
				"Module VCT3000C02V1 Entry"
			INDEX { vct3000c02v1Index }
			::= { vct3000c02v1Table 1 }

			Vct3000c02v1Entry ::=
			SEQUENCE {
				vct3000c02v1Index
				ModuleIndex,
				vct3000c02v1Mode
				ChgOverMode1,
				vct3000c02v1ModeTrapEnable
				AlarmEnable,
				vct3000c02v1Input
				ChgOverInput1,
				vct3000c02v1InputTrapEnable
				AlarmEnable,
				vct3000c02v1Gpi0
				Bit0Ina1Act,
				vct3000c02v1Gpi1
				Bit0Ina1Act,
				vct3000c02v1MainFail
				BitFail,
				vct3000c02v1MainFailTrapEnable
				AlarmEnable,
				vct3000c02v1ResFail
				BitFail,
				vct3000c02v1ResFailTrapEnable
				AlarmEnable
			 }

		-- 1.3.6.1.4.1.10106.3.101291.1.1.1
		vct3000c02v1Index OBJECT-TYPE
			SYNTAX ModuleIndex
			MAX-ACCESS read-only
			STATUS current
			DESCRIPTION
				"Index of VCT3000C02V1 Table"
		::= { vct3000c02v1Entry 1 }

		-- 1.3.6.1.4.1.10106.3.101291.1.1.3
		vct3000c02v1Mode OBJECT-TYPE
			SYNTAX ChgOverMode1
			MAX-ACCESS read-write
			STATUS current
			DESCRIPTION
				"Allows selecting the switching mode"
		::= { vct3000c02v1Entry 3 }

		-- 1.3.6.1.4.1.10106.3.101291.1.1.4
		vct3000c02v1ModeTrapEnable OBJECT-TYPE
			SYNTAX AlarmEnable
			MAX-ACCESS read-write
			STATUS current
			DESCRIPTION
				"Allows selecting the switching mode Trap Enable"
		::= { vct3000c02v1Entry 4 }

		-- 1.3.6.1.4.1.10106.3.101291.1.1.5
		vct3000c02v1Input OBJECT-TYPE
			SYNTAX ChgOverInput1
			MAX-ACCESS read-write
			STATUS current
			DESCRIPTION
				"Selected input"
		::= { vct3000c02v1Entry 5 }

		-- 1.3.6.1.4.1.10106.3.101291.1.1.6
		vct3000c02v1InputTrapEnable OBJECT-TYPE
			SYNTAX AlarmEnable
			MAX-ACCESS read-write
			STATUS current
			DESCRIPTION
				"Selected input Trap Enable"
		::= { vct3000c02v1Entry 6 }

		-- 1.3.6.1.4.1.10106.3.101291.1.1.7
		vct3000c02v1Gpi0 OBJECT-TYPE
			SYNTAX Bit0Ina1Act
			MAX-ACCESS read-only
			STATUS current
			DESCRIPTION
				"GPI0 input status"
		::= { vct3000c02v1Entry 7 }

		-- 1.3.6.1.4.1.10106.3.101291.1.1.9
		vct3000c02v1Gpi1 OBJECT-TYPE
			SYNTAX Bit0Ina1Act
			MAX-ACCESS read-only
			STATUS current
			DESCRIPTION
				"GPI1 input status"
		::= { vct3000c02v1Entry 9 }

		-- 1.3.6.1.4.1.10106.3.101291.1.1.11
		vct3000c02v1MainFail OBJECT-TYPE
			SYNTAX BitFail
			MAX-ACCESS read-only
			STATUS current
			DESCRIPTION
				"Main input status"
		::= { vct3000c02v1Entry 11 }

		-- 1.3.6.1.4.1.10106.3.101291.1.1.12
		vct3000c02v1MainFailTrapEnable OBJECT-TYPE
			SYNTAX AlarmEnable
			MAX-ACCESS read-write
			STATUS current
			DESCRIPTION
				"Main input status Trap Enable"
		::= { vct3000c02v1Entry 12 }

		-- 1.3.6.1.4.1.10106.3.101291.1.1.13
		vct3000c02v1ResFail OBJECT-TYPE
			SYNTAX BitFail
			MAX-ACCESS read-only
			STATUS current
			DESCRIPTION
				"Reserve input status"
		::= { vct3000c02v1Entry 13 }

		-- 1.3.6.1.4.1.10106.3.101291.1.1.14
		vct3000c02v1ResFailTrapEnable OBJECT-TYPE
			SYNTAX AlarmEnable
			MAX-ACCESS read-write
			STATUS current
			DESCRIPTION
				"Reserve input status Trap Enable"
		::= { vct3000c02v1Entry 14 }

		-- 1.3.6.1.4.1.10106.3.126201
		vct3000c04v1 OBJECT IDENTIFIER ::= { albalaProducts 126201 }

		-- 1.3.6.1.4.1.10106.3.126201.1
		vct3000c04v1Table  OBJECT-TYPE
			SYNTAX SEQUENCE OF Vct3000c04v1Entry
			MAX-ACCESS not-accessible
			STATUS current
			DESCRIPTION
				"Module  VCT3000C04V1 Table"
			::= { vct3000c04v1 1 }

		-- 1.3.6.1.4.1.10106.3.126201.1.1
		vct3000c04v1Entry  OBJECT-TYPE
			SYNTAX Vct3000c04v1Entry
			MAX-ACCESS not-accessible
			STATUS current
			DESCRIPTION
				"Module VCT3000C04V1 Entry"
			INDEX { vct3000c04v1Index }
			::= { vct3000c04v1Table 1 }

			Vct3000c04v1Entry ::=
			SEQUENCE {
				vct3000c04v1Index
				ModuleIndex,
				vct3000c04v1Mode
				ChgOverMode1,
				vct3000c04v1ModeTrapEnable
				AlarmEnable,
				vct3000c04v1Input
				ChgOverInput1,
				vct3000c04v1InputTrapEnable
				AlarmEnable,
				vct3000c04v1Gpi0
				Bit0Ina1Act,
				vct3000c04v1Gpi1
				Bit0Ina1Act,
				vct3000c04v1MainFail
				BitFail,
				vct3000c04v1MainFailTrapEnable
				AlarmEnable,
				vct3000c04v1ResFail
				BitFail,
				vct3000c04v1ResFailTrapEnable
				AlarmEnable
			 }

		-- 1.3.6.1.4.1.10106.3.101291.1.1.1
		vct3000c04v1Index OBJECT-TYPE
			SYNTAX ModuleIndex
			MAX-ACCESS read-only
			STATUS current
			DESCRIPTION
				"Index of VCT3000C04V1 Table"
		::= { vct3000c04v1Entry 1 }

		-- 1.3.6.1.4.1.10106.3.101291.1.1.3
		vct3000c04v1Mode OBJECT-TYPE
			SYNTAX ChgOverMode1
			MAX-ACCESS read-write
			STATUS current
			DESCRIPTION
				"Allows selecting the switching mode"
		::= { vct3000c04v1Entry 3 }

		-- 1.3.6.1.4.1.10106.3.101291.1.1.4
		vct3000c04v1ModeTrapEnable OBJECT-TYPE
			SYNTAX AlarmEnable
			MAX-ACCESS read-write
			STATUS current
			DESCRIPTION
				"Allows selecting the switching mode Trap Enable"
		::= { vct3000c04v1Entry 4 }

		-- 1.3.6.1.4.1.10106.3.101291.1.1.5
		vct3000c04v1Input OBJECT-TYPE
			SYNTAX ChgOverInput1
			MAX-ACCESS read-write
			STATUS current
			DESCRIPTION
				"Selected input"
		::= { vct3000c04v1Entry 5 }

		-- 1.3.6.1.4.1.10106.3.101291.1.1.6
		vct3000c04v1InputTrapEnable OBJECT-TYPE
			SYNTAX AlarmEnable
			MAX-ACCESS read-write
			STATUS current
			DESCRIPTION
				"Selected input Trap Enable"
		::= { vct3000c04v1Entry 6 }

		-- 1.3.6.1.4.1.10106.3.101291.1.1.7
		vct3000c04v1Gpi0 OBJECT-TYPE
			SYNTAX Bit0Ina1Act
			MAX-ACCESS read-only
			STATUS current
			DESCRIPTION
				"GPI0 input status"
		::= { vct3000c04v1Entry 7 }

		-- 1.3.6.1.4.1.10106.3.101291.1.1.9
		vct3000c04v1Gpi1 OBJECT-TYPE
			SYNTAX Bit0Ina1Act
			MAX-ACCESS read-only
			STATUS current
			DESCRIPTION
				"GPI1 input status"
		::= { vct3000c04v1Entry 9 }

		-- 1.3.6.1.4.1.10106.3.101291.1.1.11
		vct3000c04v1MainFail OBJECT-TYPE
			SYNTAX BitFail
			MAX-ACCESS read-only
			STATUS current
			DESCRIPTION
				"Main input status"
		::= { vct3000c04v1Entry 11 }

		-- 1.3.6.1.4.1.10106.3.101291.1.1.12
		vct3000c04v1MainFailTrapEnable OBJECT-TYPE
			SYNTAX AlarmEnable
			MAX-ACCESS read-write
			STATUS current
			DESCRIPTION
				"Main input status Trap Enable"
		::= { vct3000c04v1Entry 12 }

		-- 1.3.6.1.4.1.10106.3.101291.1.1.13
		vct3000c04v1ResFail OBJECT-TYPE
			SYNTAX BitFail
			MAX-ACCESS read-only
			STATUS current
			DESCRIPTION
				"Reserve input status"
		::= { vct3000c04v1Entry 13 }

		-- 1.3.6.1.4.1.10106.3.101291.1.1.14
		vct3000c04v1ResFailTrapEnable OBJECT-TYPE
			SYNTAX AlarmEnable
			MAX-ACCESS read-write
			STATUS current
			DESCRIPTION
				"Reserve input status Trap Enable"
		::= { vct3000c04v1Entry 14 }

		-- 1.3.6.1.4.1.10106.3.126301
		vct3000c05v1 OBJECT IDENTIFIER ::= { albalaProducts 126301 }

		-- 1.3.6.1.4.1.10106.3.126301.1
		vct3000c05v1Table  OBJECT-TYPE
			SYNTAX SEQUENCE OF Vct3000c05v1Entry
			MAX-ACCESS not-accessible
			STATUS current
			DESCRIPTION
				"Module  VCT3000C05V1 Table"
			::= { vct3000c05v1 1 }

		-- 1.3.6.1.4.1.10106.3.126301.1.1
		vct3000c05v1Entry  OBJECT-TYPE
			SYNTAX Vct3000c05v1Entry
			MAX-ACCESS not-accessible
			STATUS current
			DESCRIPTION
				"Module VCT3000C05V1 Entry"
			INDEX { vct3000c05v1Index }
			::= { vct3000c05v1Table 1 }

			Vct3000c05v1Entry ::=
			SEQUENCE {
				vct3000c05v1Index
				ModuleIndex,
				vct3000c05v1Mode
				ChgOverMode1,
				vct3000c05v1ModeTrapEnable
				AlarmEnable,
				vct3000c05v1Input
				ChgOverInput1,
				vct3000c05v1InputTrapEnable
				AlarmEnable,
				vct3000c05v1Gpi0
				Bit0Ina1Act,
				vct3000c05v1Gpi1
				Bit0Ina1Act,
				vct3000c05v1MainFail
				BitFail,
				vct3000c05v1MainFailTrapEnable
				AlarmEnable,
				vct3000c05v1ResFail
				BitFail,
				vct3000c05v1ResFailTrapEnable
				AlarmEnable
			 }

		-- 1.3.6.1.4.1.10106.3.101291.1.1.1
		vct3000c05v1Index OBJECT-TYPE
			SYNTAX ModuleIndex
			MAX-ACCESS read-only
			STATUS current
			DESCRIPTION
				"Index of VCT3000C05V1 Table"
		::= { vct3000c05v1Entry 1 }

		-- 1.3.6.1.4.1.10106.3.101291.1.1.3
		vct3000c05v1Mode OBJECT-TYPE
			SYNTAX ChgOverMode1
			MAX-ACCESS read-write
			STATUS current
			DESCRIPTION
				"Allows selecting the switching mode"
		::= { vct3000c05v1Entry 3 }

		-- 1.3.6.1.4.1.10106.3.101291.1.1.4
		vct3000c05v1ModeTrapEnable OBJECT-TYPE
			SYNTAX AlarmEnable
			MAX-ACCESS read-write
			STATUS current
			DESCRIPTION
				"Allows selecting the switching mode Trap Enable"
		::= { vct3000c05v1Entry 4 }

		-- 1.3.6.1.4.1.10106.3.101291.1.1.5
		vct3000c05v1Input OBJECT-TYPE
			SYNTAX ChgOverInput1
			MAX-ACCESS read-write
			STATUS current
			DESCRIPTION
				"Selected input"
		::= { vct3000c05v1Entry 5 }

		-- 1.3.6.1.4.1.10106.3.101291.1.1.6
		vct3000c05v1InputTrapEnable OBJECT-TYPE
			SYNTAX AlarmEnable
			MAX-ACCESS read-write
			STATUS current
			DESCRIPTION
				"Selected input Trap Enable"
		::= { vct3000c05v1Entry 6 }

		-- 1.3.6.1.4.1.10106.3.101291.1.1.7
		vct3000c05v1Gpi0 OBJECT-TYPE
			SYNTAX Bit0Ina1Act
			MAX-ACCESS read-only
			STATUS current
			DESCRIPTION
				"GPI0 input status"
		::= { vct3000c05v1Entry 7 }

		-- 1.3.6.1.4.1.10106.3.101291.1.1.9
		vct3000c05v1Gpi1 OBJECT-TYPE
			SYNTAX Bit0Ina1Act
			MAX-ACCESS read-only
			STATUS current
			DESCRIPTION
				"GPI1 input status"
		::= { vct3000c05v1Entry 9 }

		-- 1.3.6.1.4.1.10106.3.101291.1.1.11
		vct3000c05v1MainFail OBJECT-TYPE
			SYNTAX BitFail
			MAX-ACCESS read-only
			STATUS current
			DESCRIPTION
				"Main input status"
		::= { vct3000c05v1Entry 11 }

		-- 1.3.6.1.4.1.10106.3.101291.1.1.12
		vct3000c05v1MainFailTrapEnable OBJECT-TYPE
			SYNTAX AlarmEnable
			MAX-ACCESS read-write
			STATUS current
			DESCRIPTION
				"Main input status Trap Enable"
		::= { vct3000c05v1Entry 12 }

		-- 1.3.6.1.4.1.10106.3.101291.1.1.13
		vct3000c05v1ResFail OBJECT-TYPE
			SYNTAX BitFail
			MAX-ACCESS read-only
			STATUS current
			DESCRIPTION
				"Reserve input status"
		::= { vct3000c05v1Entry 13 }

		-- 1.3.6.1.4.1.10106.3.101291.1.1.14
		vct3000c05v1ResFailTrapEnable OBJECT-TYPE
			SYNTAX AlarmEnable
			MAX-ACCESS read-write
			STATUS current
			DESCRIPTION
				"Reserve input status Trap Enable"
		::= { vct3000c05v1Entry 14 }

		-- 1.3.6.1.4.1.10106.3.128301
		dvm3000p01v1 OBJECT IDENTIFIER ::= { albalaProducts 128301 }

		-- 1.3.6.1.4.1.10106.3.128301.1
		dvm3000p01v1Table  OBJECT-TYPE
			SYNTAX SEQUENCE OF Dvm3000p01v1Entry
			MAX-ACCESS not-accessible
			STATUS current
			DESCRIPTION
				"Module  DVM3000P01V1 Table"
			::= { dvm3000p01v1 1 }

		-- 1.3.6.1.4.1.10106.3.128301.1.1
		dvm3000p01v1Entry  OBJECT-TYPE
			SYNTAX Dvm3000p01v1Entry
			MAX-ACCESS not-accessible
			STATUS current
			DESCRIPTION
				"Module DVM3000P01V1 Entry"
			INDEX { dvm3000p01v1Index }
			::= { dvm3000p01v1Table 1 }

			Dvm3000p01v1Entry ::=
			SEQUENCE {
				dvm3000p01v1Index
				ModuleIndex,
				dvm3000p01v1Chroma
				Bit0Off1On,
				dvm3000p01v1LowPassFilter
				Bit0Ext1Nor,
				dvm3000p01v1VbiPass
				Bit0Bnk1Pas,
				dvm3000p01v1Mode
				Bit05251625,
				dvm3000p01v1NoSigA
				BitFail,
				dvm3000p01v1NoSigATrapEnable
				AlarmEnable,
				dvm3000p01v1MaxEqA
				BitFail,
				dvm3000p01v1NoSigB
				BitFail,
				dvm3000p01v1NoSigBTrapEnable
				AlarmEnable,
				dvm3000p01v1MaxEqB
				BitFail
			 }

		-- 1.3.6.1.4.1.10106.3.101291.1.1.1
		dvm3000p01v1Index OBJECT-TYPE
			SYNTAX ModuleIndex
			MAX-ACCESS read-only
			STATUS current
			DESCRIPTION
				"Index of DVM3000P01V1 Table"
		::= { dvm3000p01v1Entry 1 }

		-- 1.3.6.1.4.1.10106.3.101291.1.1.3
		dvm3000p01v1Chroma OBJECT-TYPE
			SYNTAX Bit0Off1On
			MAX-ACCESS read-write
			STATUS current
			DESCRIPTION
				"Allows disabling chroma"
		::= { dvm3000p01v1Entry 3 }

		-- 1.3.6.1.4.1.10106.3.101291.1.1.5
		dvm3000p01v1LowPassFilter OBJECT-TYPE
			SYNTAX Bit0Ext1Nor
			MAX-ACCESS read-write
			STATUS current
			DESCRIPTION
				"Allows selecting low pass filter"
		::= { dvm3000p01v1Entry 5 }

		-- 1.3.6.1.4.1.10106.3.101291.1.1.7
		dvm3000p01v1VbiPass OBJECT-TYPE
			SYNTAX Bit0Bnk1Pas
			MAX-ACCESS read-write
			STATUS current
			DESCRIPTION
				"Allows selecting if the VBI is blanked"
		::= { dvm3000p01v1Entry 7 }

		-- 1.3.6.1.4.1.10106.3.101291.1.1.9
		dvm3000p01v1Mode OBJECT-TYPE
			SYNTAX Bit05251625
			MAX-ACCESS read-write
			STATUS current
			DESCRIPTION
				"Allows selecting signal type"
		::= { dvm3000p01v1Entry 9 }

		-- 1.3.6.1.4.1.10106.3.101291.1.1.11
		dvm3000p01v1NoSigA OBJECT-TYPE
			SYNTAX BitFail
			MAX-ACCESS read-only
			STATUS current
			DESCRIPTION
				"Input signal status"
		::= { dvm3000p01v1Entry 11 }

		-- 1.3.6.1.4.1.10106.3.101291.1.1.12
		dvm3000p01v1NoSigATrapEnable OBJECT-TYPE
			SYNTAX AlarmEnable
			MAX-ACCESS read-write
			STATUS current
			DESCRIPTION
				"Input signal status Trap Enable"
		::= { dvm3000p01v1Entry 12 }

		-- 1.3.6.1.4.1.10106.3.101291.1.1.13
		dvm3000p01v1MaxEqA OBJECT-TYPE
			SYNTAX BitFail
			MAX-ACCESS read-only
			STATUS current
			DESCRIPTION
				"Indicates maximum equalization"
		::= { dvm3000p01v1Entry 13 }

		-- 1.3.6.1.4.1.10106.3.101291.1.1.15
		dvm3000p01v1NoSigB OBJECT-TYPE
			SYNTAX BitFail
			MAX-ACCESS read-only
			STATUS current
			DESCRIPTION
				"Input signal status"
		::= { dvm3000p01v1Entry 15 }

		-- 1.3.6.1.4.1.10106.3.101291.1.1.16
		dvm3000p01v1NoSigBTrapEnable OBJECT-TYPE
			SYNTAX AlarmEnable
			MAX-ACCESS read-write
			STATUS current
			DESCRIPTION
				"Input signal status Trap Enable"
		::= { dvm3000p01v1Entry 16 }

		-- 1.3.6.1.4.1.10106.3.101291.1.1.17
		dvm3000p01v1MaxEqB OBJECT-TYPE
			SYNTAX BitFail
			MAX-ACCESS read-only
			STATUS current
			DESCRIPTION
				"Indicates maximum equalization"
		::= { dvm3000p01v1Entry 17 }

		-- 1.3.6.1.4.1.10106.3.128701
		tpg3000p01v1 OBJECT IDENTIFIER ::= { albalaProducts 128701 }

		-- 1.3.6.1.4.1.10106.3.128701.1
		tpg3000p01v1Table  OBJECT-TYPE
			SYNTAX SEQUENCE OF Tpg3000p01v1Entry
			MAX-ACCESS not-accessible
			STATUS current
			DESCRIPTION
				"Module  TPG3000P01V1 Table"
			::= { tpg3000p01v1 1 }

		-- 1.3.6.1.4.1.10106.3.128701.1.1
		tpg3000p01v1Entry  OBJECT-TYPE
			SYNTAX Tpg3000p01v1Entry
			MAX-ACCESS not-accessible
			STATUS current
			DESCRIPTION
				"Module TPG3000P01V1 Entry"
			INDEX { tpg3000p01v1Index }
			::= { tpg3000p01v1Table 1 }

			Tpg3000p01v1Entry ::=
			SEQUENCE {
				tpg3000p01v1Index
				ModuleIndex,
				tpg3000p01v1ColourBars
				Bit0No1Yes,
				tpg3000p01v1Text
				Bit0No1Yes,
				tpg3000p01v1Lines
				Bit05251625,
				tpg3000p01v1Char1
				CaptChar1,
				tpg3000p01v1Char2
				CaptChar1,
				tpg3000p01v1Char3
				CaptChar1,
				tpg3000p01v1Char4
				CaptChar1,
				tpg3000p01v1Char5
				CaptChar1,
				tpg3000p01v1Char6
				CaptChar1,
				tpg3000p01v1Char7
				CaptChar1,
				tpg3000p01v1Char8
				CaptChar1,
				tpg3000p01v1TextForeColour
				CaptColour1,
				tpg3000p01v1TextBackColour
				CaptColour1
			 }

		-- 1.3.6.1.4.1.10106.3.101291.1.1.1
		tpg3000p01v1Index OBJECT-TYPE
			SYNTAX ModuleIndex
			MAX-ACCESS read-only
			STATUS current
			DESCRIPTION
				"Index of TPG3000P01V1 Table"
		::= { tpg3000p01v1Entry 1 }

		-- 1.3.6.1.4.1.10106.3.101291.1.1.3
		tpg3000p01v1ColourBars OBJECT-TYPE
			SYNTAX Bit0No1Yes
			MAX-ACCESS read-write
			STATUS current
			DESCRIPTION
				"Allows enabling colour bars in four outputs"
		::= { tpg3000p01v1Entry 3 }

		-- 1.3.6.1.4.1.10106.3.101291.1.1.5
		tpg3000p01v1Text OBJECT-TYPE
			SYNTAX Bit0No1Yes
			MAX-ACCESS read-write
			STATUS current
			DESCRIPTION
				"Allows enabling caption text"
		::= { tpg3000p01v1Entry 5 }

		-- 1.3.6.1.4.1.10106.3.101291.1.1.7
		tpg3000p01v1Lines OBJECT-TYPE
			SYNTAX Bit05251625
			MAX-ACCESS read-write
			STATUS current
			DESCRIPTION
				"TV output signal format"
		::= { tpg3000p01v1Entry 7 }

		-- 1.3.6.1.4.1.10106.3.101291.1.1.9
		tpg3000p01v1Char1 OBJECT-TYPE
			SYNTAX CaptChar1
			MAX-ACCESS read-write
			STATUS current
			DESCRIPTION
				"Caption character 1"
		::= { tpg3000p01v1Entry 9 }

		-- 1.3.6.1.4.1.10106.3.101291.1.1.11
		tpg3000p01v1Char2 OBJECT-TYPE
			SYNTAX CaptChar1
			MAX-ACCESS read-write
			STATUS current
			DESCRIPTION
				"Caption character 2"
		::= { tpg3000p01v1Entry 11 }

		-- 1.3.6.1.4.1.10106.3.101291.1.1.13
		tpg3000p01v1Char3 OBJECT-TYPE
			SYNTAX CaptChar1
			MAX-ACCESS read-write
			STATUS current
			DESCRIPTION
				"Caption character 3"
		::= { tpg3000p01v1Entry 13 }

		-- 1.3.6.1.4.1.10106.3.101291.1.1.15
		tpg3000p01v1Char4 OBJECT-TYPE
			SYNTAX CaptChar1
			MAX-ACCESS read-write
			STATUS current
			DESCRIPTION
				"Caption character 4"
		::= { tpg3000p01v1Entry 15 }

		-- 1.3.6.1.4.1.10106.3.101291.1.1.17
		tpg3000p01v1Char5 OBJECT-TYPE
			SYNTAX CaptChar1
			MAX-ACCESS read-write
			STATUS current
			DESCRIPTION
				"Caption character 5"
		::= { tpg3000p01v1Entry 17 }

		-- 1.3.6.1.4.1.10106.3.101291.1.1.19
		tpg3000p01v1Char6 OBJECT-TYPE
			SYNTAX CaptChar1
			MAX-ACCESS read-write
			STATUS current
			DESCRIPTION
				"Caption character 6"
		::= { tpg3000p01v1Entry 19 }

		-- 1.3.6.1.4.1.10106.3.101291.1.1.21
		tpg3000p01v1Char7 OBJECT-TYPE
			SYNTAX CaptChar1
			MAX-ACCESS read-write
			STATUS current
			DESCRIPTION
				"Caption character 7"
		::= { tpg3000p01v1Entry 21 }

		-- 1.3.6.1.4.1.10106.3.101291.1.1.23
		tpg3000p01v1Char8 OBJECT-TYPE
			SYNTAX CaptChar1
			MAX-ACCESS read-write
			STATUS current
			DESCRIPTION
				"Caption character 8"
		::= { tpg3000p01v1Entry 23 }

		-- 1.3.6.1.4.1.10106.3.101291.1.1.25
		tpg3000p01v1TextForeColour OBJECT-TYPE
			SYNTAX CaptColour1
			MAX-ACCESS read-write
			STATUS current
			DESCRIPTION
				"Allows selecting caption foreground colour"
		::= { tpg3000p01v1Entry 25 }

		-- 1.3.6.1.4.1.10106.3.101291.1.1.27
		tpg3000p01v1TextBackColour OBJECT-TYPE
			SYNTAX CaptColour1
			MAX-ACCESS read-write
			STATUS current
			DESCRIPTION
				"Allows selecting caption background colour"
		::= { tpg3000p01v1Entry 27 }

		-- 1.3.6.1.4.1.10106.3.129101
		dsw3000p01v1 OBJECT IDENTIFIER ::= { albalaProducts 129101 }

		-- 1.3.6.1.4.1.10106.3.129101.1
		dsw3000p01v1Table  OBJECT-TYPE
			SYNTAX SEQUENCE OF Dsw3000p01v1Entry
			MAX-ACCESS not-accessible
			STATUS current
			DESCRIPTION
				"Module  DSW3000P01V1 Table"
			::= { dsw3000p01v1 1 }

		-- 1.3.6.1.4.1.10106.3.129101.1.1
		dsw3000p01v1Entry  OBJECT-TYPE
			SYNTAX Dsw3000p01v1Entry
			MAX-ACCESS not-accessible
			STATUS current
			DESCRIPTION
				"Module DSW3000P01V1 Entry"
			INDEX { dsw3000p01v1Index }
			::= { dsw3000p01v1Table 1 }

			Dsw3000p01v1Entry ::=
			SEQUENCE {
				dsw3000p01v1Index
				ModuleIndex,
				dsw3000p01v1Mode
				ChgOverMode2,
				dsw3000p01v1ModeTrapEnable
				AlarmEnable,
				dsw3000p01v1Buzzer
				BitMask,
				dsw3000p01v1Input
				ChgOverInput1,
				dsw3000p01v1InputTrapEnable
				AlarmEnable,
				dsw3000p01v1MainFail
				BitFail,
				dsw3000p01v1MainFailTrapEnable
				AlarmEnable,
				dsw3000p01v1ExtMainFail
				BitFail,
				dsw3000p01v1ExtMainFailTrapEnable
				AlarmEnable,
				dsw3000p01v1ResFail
				BitFail,
				dsw3000p01v1ResFailTrapEnable
				AlarmEnable,
				dsw3000p01v1ExtResFail
				BitFail,
				dsw3000p01v1ExtResFailTrapEnable
				AlarmEnable,
				dsw3000p01v1AuxFail
				BitFail,
				dsw3000p01v1AuxFailTrapEnable
				AlarmEnable,
				dsw3000p01v1ExtAuxFail
				BitFail,
				dsw3000p01v1ExtAuxFailTrapEnable
				AlarmEnable
			 }

		-- 1.3.6.1.4.1.10106.3.101291.1.1.1
		dsw3000p01v1Index OBJECT-TYPE
			SYNTAX ModuleIndex
			MAX-ACCESS read-only
			STATUS current
			DESCRIPTION
				"Index of DSW3000P01V1 Table"
		::= { dsw3000p01v1Entry 1 }

		-- 1.3.6.1.4.1.10106.3.101291.1.1.3
		dsw3000p01v1Mode OBJECT-TYPE
			SYNTAX ChgOverMode2
			MAX-ACCESS read-write
			STATUS current
			DESCRIPTION
				"Allows selecting the switching mode"
		::= { dsw3000p01v1Entry 3 }

		-- 1.3.6.1.4.1.10106.3.101291.1.1.4
		dsw3000p01v1ModeTrapEnable OBJECT-TYPE
			SYNTAX AlarmEnable
			MAX-ACCESS read-write
			STATUS current
			DESCRIPTION
				"Allows selecting the switching mode Trap Enable"
		::= { dsw3000p01v1Entry 4 }

		-- 1.3.6.1.4.1.10106.3.101291.1.1.5
		dsw3000p01v1Buzzer OBJECT-TYPE
			SYNTAX BitMask
			MAX-ACCESS read-write
			STATUS current
			DESCRIPTION
				"Allows buzzer operation"
		::= { dsw3000p01v1Entry 5 }

		-- 1.3.6.1.4.1.10106.3.101291.1.1.7
		dsw3000p01v1Input OBJECT-TYPE
			SYNTAX ChgOverInput1
			MAX-ACCESS read-write
			STATUS current
			DESCRIPTION
				"Selected input"
		::= { dsw3000p01v1Entry 7 }

		-- 1.3.6.1.4.1.10106.3.101291.1.1.8
		dsw3000p01v1InputTrapEnable OBJECT-TYPE
			SYNTAX AlarmEnable
			MAX-ACCESS read-write
			STATUS current
			DESCRIPTION
				"Selected input Trap Enable"
		::= { dsw3000p01v1Entry 8 }

		-- 1.3.6.1.4.1.10106.3.101291.1.1.9
		dsw3000p01v1MainFail OBJECT-TYPE
			SYNTAX BitFail
			MAX-ACCESS read-only
			STATUS current
			DESCRIPTION
				"Main input status"
		::= { dsw3000p01v1Entry 9 }

		-- 1.3.6.1.4.1.10106.3.101291.1.1.10
		dsw3000p01v1MainFailTrapEnable OBJECT-TYPE
			SYNTAX AlarmEnable
			MAX-ACCESS read-write
			STATUS current
			DESCRIPTION
				"Main input status Trap Enable"
		::= { dsw3000p01v1Entry 10 }

		-- 1.3.6.1.4.1.10106.3.101291.1.1.11
		dsw3000p01v1ExtMainFail OBJECT-TYPE
			SYNTAX BitFail
			MAX-ACCESS read-only
			STATUS current
			DESCRIPTION
				"Main external input fail status"
		::= { dsw3000p01v1Entry 11 }

		-- 1.3.6.1.4.1.10106.3.101291.1.1.12
		dsw3000p01v1ExtMainFailTrapEnable OBJECT-TYPE
			SYNTAX AlarmEnable
			MAX-ACCESS read-write
			STATUS current
			DESCRIPTION
				"Main external input fail status Trap Enable"
		::= { dsw3000p01v1Entry 12 }

		-- 1.3.6.1.4.1.10106.3.101291.1.1.13
		dsw3000p01v1ResFail OBJECT-TYPE
			SYNTAX BitFail
			MAX-ACCESS read-only
			STATUS current
			DESCRIPTION
				"Reserve input status"
		::= { dsw3000p01v1Entry 13 }

		-- 1.3.6.1.4.1.10106.3.101291.1.1.14
		dsw3000p01v1ResFailTrapEnable OBJECT-TYPE
			SYNTAX AlarmEnable
			MAX-ACCESS read-write
			STATUS current
			DESCRIPTION
				"Reserve input status Trap Enable"
		::= { dsw3000p01v1Entry 14 }

		-- 1.3.6.1.4.1.10106.3.101291.1.1.15
		dsw3000p01v1ExtResFail OBJECT-TYPE
			SYNTAX BitFail
			MAX-ACCESS read-only
			STATUS current
			DESCRIPTION
				"Reserve external input fail status"
		::= { dsw3000p01v1Entry 15 }

		-- 1.3.6.1.4.1.10106.3.101291.1.1.16
		dsw3000p01v1ExtResFailTrapEnable OBJECT-TYPE
			SYNTAX AlarmEnable
			MAX-ACCESS read-write
			STATUS current
			DESCRIPTION
				"Reserve external input fail status Trap Enable"
		::= { dsw3000p01v1Entry 16 }

		-- 1.3.6.1.4.1.10106.3.101291.1.1.17
		dsw3000p01v1AuxFail OBJECT-TYPE
			SYNTAX BitFail
			MAX-ACCESS read-only
			STATUS current
			DESCRIPTION
				"Auxiliar input status"
		::= { dsw3000p01v1Entry 17 }

		-- 1.3.6.1.4.1.10106.3.101291.1.1.18
		dsw3000p01v1AuxFailTrapEnable OBJECT-TYPE
			SYNTAX AlarmEnable
			MAX-ACCESS read-write
			STATUS current
			DESCRIPTION
				"Auxiliar input status Trap Enable"
		::= { dsw3000p01v1Entry 18 }

		-- 1.3.6.1.4.1.10106.3.101291.1.1.19
		dsw3000p01v1ExtAuxFail OBJECT-TYPE
			SYNTAX BitFail
			MAX-ACCESS read-only
			STATUS current
			DESCRIPTION
				"Auxiliar external input fail status"
		::= { dsw3000p01v1Entry 19 }

		-- 1.3.6.1.4.1.10106.3.101291.1.1.20
		dsw3000p01v1ExtAuxFailTrapEnable OBJECT-TYPE
			SYNTAX AlarmEnable
			MAX-ACCESS read-write
			STATUS current
			DESCRIPTION
				"Auxiliar external input fail status Trap Enable"
		::= { dsw3000p01v1Entry 20 }

		-- 1.3.6.1.4.1.10106.3.130101
		lns3000p01v1 OBJECT IDENTIFIER ::= { albalaProducts 130101 }

		-- 1.3.6.1.4.1.10106.3.130101.1
		lns3000p01v1Table  OBJECT-TYPE
			SYNTAX SEQUENCE OF Lns3000p01v1Entry
			MAX-ACCESS not-accessible
			STATUS current
			DESCRIPTION
				"Module  LNS3000P01V1 Table"
			::= { lns3000p01v1 1 }

		-- 1.3.6.1.4.1.10106.3.130101.1.1
		lns3000p01v1Entry  OBJECT-TYPE
			SYNTAX Lns3000p01v1Entry
			MAX-ACCESS not-accessible
			STATUS current
			DESCRIPTION
				"Module LNS3000P01V1 Entry"
			INDEX { lns3000p01v1Index }
			::= { lns3000p01v1Table 1 }

			Lns3000p01v1Entry ::=
			SEQUENCE {
				lns3000p01v1Index
				ModuleIndex,
				lns3000p01v1LumaGain
				GainLin1,
				lns3000p01v1ChromaGain
				GainLin1,
				lns3000p01v1BlackOffset
				BlackOffset2,
				lns3000p01v1Mode
				Bit0Pro1Syn,
				lns3000p01v1SyncOut
				Bit0412,
				lns3000p01v1NoSignalPgm
				BitFail,
				lns3000p01v1NoSignalPgmTrapEnable
				AlarmEnable,
				lns3000p01v1EdhChkPgm
				BitFail,
				lns3000p01v1TimingErr
				BitFail,
				lns3000p01v1TimingErrTrapEnable
				AlarmEnable,
				lns3000p01v1NoSignalRef
				BitFail,
				lns3000p01v1NoSignalRefTrapEnable
				AlarmEnable,
				lns3000p01v1EdhChkRef
				BitFail
			 }

		-- 1.3.6.1.4.1.10106.3.101291.1.1.1
		lns3000p01v1Index OBJECT-TYPE
			SYNTAX ModuleIndex
			MAX-ACCESS read-only
			STATUS current
			DESCRIPTION
				"Index of LNS3000P01V1 Table"
		::= { lns3000p01v1Entry 1 }

		-- 1.3.6.1.4.1.10106.3.101291.1.1.3
		lns3000p01v1LumaGain OBJECT-TYPE
			SYNTAX GainLin1
			MAX-ACCESS read-write
			STATUS current
			DESCRIPTION
				"Allows adjusting the luma gain"
		::= { lns3000p01v1Entry 3 }

		-- 1.3.6.1.4.1.10106.3.101291.1.1.5
		lns3000p01v1ChromaGain OBJECT-TYPE
			SYNTAX GainLin1
			MAX-ACCESS read-write
			STATUS current
			DESCRIPTION
				"Allows adjusting the chorma gain"
		::= { lns3000p01v1Entry 5 }

		-- 1.3.6.1.4.1.10106.3.101291.1.1.7
		lns3000p01v1BlackOffset OBJECT-TYPE
			SYNTAX BlackOffset2
			MAX-ACCESS read-write
			STATUS current
			DESCRIPTION
				"Allows adjusting the black offset"
		::= { lns3000p01v1Entry 7 }

		-- 1.3.6.1.4.1.10106.3.101291.1.1.9
		lns3000p01v1Mode OBJECT-TYPE
			SYNTAX Bit0Pro1Syn
			MAX-ACCESS read-write
			STATUS current
			DESCRIPTION
				"Allows selecting the operating mode"
		::= { lns3000p01v1Entry 9 }

		-- 1.3.6.1.4.1.10106.3.101291.1.1.11
		lns3000p01v1SyncOut OBJECT-TYPE
			SYNTAX Bit0412
			MAX-ACCESS read-write
			STATUS current
			DESCRIPTION
				"Allows selectiing the number of synchronized outputs"
		::= { lns3000p01v1Entry 11 }

		-- 1.3.6.1.4.1.10106.3.101291.1.1.13
		lns3000p01v1NoSignalPgm OBJECT-TYPE
			SYNTAX BitFail
			MAX-ACCESS read-only
			STATUS current
			DESCRIPTION
				"SDI input signal status"
		::= { lns3000p01v1Entry 13 }

		-- 1.3.6.1.4.1.10106.3.101291.1.1.14
		lns3000p01v1NoSignalPgmTrapEnable OBJECT-TYPE
			SYNTAX AlarmEnable
			MAX-ACCESS read-write
			STATUS current
			DESCRIPTION
				"SDI input signal status Trap Enable"
		::= { lns3000p01v1Entry 14 }

		-- 1.3.6.1.4.1.10106.3.101291.1.1.15
		lns3000p01v1EdhChkPgm OBJECT-TYPE
			SYNTAX BitFail
			MAX-ACCESS read-only
			STATUS current
			DESCRIPTION
				"The EDH packet has wrong checksum"
		::= { lns3000p01v1Entry 15 }

		-- 1.3.6.1.4.1.10106.3.101291.1.1.17
		lns3000p01v1TimingErr OBJECT-TYPE
			SYNTAX BitFail
			MAX-ACCESS read-only
			STATUS current
			DESCRIPTION
				"Indicates that the module can not operate as line sync because the timing between inputs is does not allow it"
		::= { lns3000p01v1Entry 17 }

		-- 1.3.6.1.4.1.10106.3.101291.1.1.18
		lns3000p01v1TimingErrTrapEnable OBJECT-TYPE
			SYNTAX AlarmEnable
			MAX-ACCESS read-write
			STATUS current
			DESCRIPTION
				"Indicates that the module can not operate as line sync because the timing between inputs is does not allow it Trap Enable"
		::= { lns3000p01v1Entry 18 }

		-- 1.3.6.1.4.1.10106.3.101291.1.1.19
		lns3000p01v1NoSignalRef OBJECT-TYPE
			SYNTAX BitFail
			MAX-ACCESS read-only
			STATUS current
			DESCRIPTION
				"SDI input signal status"
		::= { lns3000p01v1Entry 19 }

		-- 1.3.6.1.4.1.10106.3.101291.1.1.20
		lns3000p01v1NoSignalRefTrapEnable OBJECT-TYPE
			SYNTAX AlarmEnable
			MAX-ACCESS read-write
			STATUS current
			DESCRIPTION
				"SDI input signal status Trap Enable"
		::= { lns3000p01v1Entry 20 }

		-- 1.3.6.1.4.1.10106.3.101291.1.1.21
		lns3000p01v1EdhChkRef OBJECT-TYPE
			SYNTAX BitFail
			MAX-ACCESS read-only
			STATUS current
			DESCRIPTION
				"The EDH packet has wrong checksum"
		::= { lns3000p01v1Entry 21 }

		-- 1.3.6.1.4.1.10106.3.131502
		dli3000p01v2 OBJECT IDENTIFIER ::= { albalaProducts 131502 }

		-- 1.3.6.1.4.1.10106.3.131502.1
		dli3000p01v2Table  OBJECT-TYPE
			SYNTAX SEQUENCE OF Dli3000p01v2Entry
			MAX-ACCESS not-accessible
			STATUS current
			DESCRIPTION
				"Module  DLI3000P01V2 Table"
			::= { dli3000p01v2 1 }

		-- 1.3.6.1.4.1.10106.3.131502.1.1
		dli3000p01v2Entry  OBJECT-TYPE
			SYNTAX Dli3000p01v2Entry
			MAX-ACCESS not-accessible
			STATUS current
			DESCRIPTION
				"Module DLI3000P01V2 Entry"
			INDEX { dli3000p01v2Index }
			::= { dli3000p01v2Table 1 }

			Dli3000p01v2Entry ::=
			SEQUENCE {
				dli3000p01v2Index
				ModuleIndex,
				dli3000p01v2LogoSdi
				Bit0Off1On,
				dli3000p01v2LogoCcvs
				Bit0Off1On,
				dli3000p01v2LoadLogo
				Bit0No1Yes,
				dli3000p01v2SelectedLogo
				Uint4,
				dli3000p01v2FadeTime
				DelayFram3,
				dli3000p01v2LogoPosH
				LogoPosH1,
				dli3000p01v2LogoSizeH
				LogoSizH1,
				dli3000p01v2LogoPosV
				LogoPosV1,
				dli3000p01v2LogoSizeV
				LogoSizV1,
				dli3000p01v2LogoMemSize
				LogoSizeKpix1,
				dli3000p01v2MaxEq
				BitFail,
				dli3000p01v2NoSig
				BitFail,
				dli3000p01v2NoSigTrapEnable
				AlarmEnable
			 }

		-- 1.3.6.1.4.1.10106.3.101291.1.1.1
		dli3000p01v2Index OBJECT-TYPE
			SYNTAX ModuleIndex
			MAX-ACCESS read-only
			STATUS current
			DESCRIPTION
				"Index of DLI3000P01V2 Table"
		::= { dli3000p01v2Entry 1 }

		-- 1.3.6.1.4.1.10106.3.101291.1.1.3
		dli3000p01v2LogoSdi OBJECT-TYPE
			SYNTAX Bit0Off1On
			MAX-ACCESS read-write
			STATUS current
			DESCRIPTION
				"Allows selecting if the logo is inserted on SDI output"
		::= { dli3000p01v2Entry 3 }

		-- 1.3.6.1.4.1.10106.3.101291.1.1.5
		dli3000p01v2LogoCcvs OBJECT-TYPE
			SYNTAX Bit0Off1On
			MAX-ACCESS read-write
			STATUS current
			DESCRIPTION
				"Allows selecting if the logo is inserted on CCVS output"
		::= { dli3000p01v2Entry 5 }

		-- 1.3.6.1.4.1.10106.3.101291.1.1.7
		dli3000p01v2LoadLogo OBJECT-TYPE
			SYNTAX Bit0No1Yes
			MAX-ACCESS read-write
			STATUS current
			DESCRIPTION
				"Allows reloading the logo after a file transfer"
		::= { dli3000p01v2Entry 7 }

		-- 1.3.6.1.4.1.10106.3.101291.1.1.9
		dli3000p01v2SelectedLogo OBJECT-TYPE
			SYNTAX Uint4
			MAX-ACCESS read-write
			STATUS current
			DESCRIPTION
				"Allows selecting the logo to be displayed"
		::= { dli3000p01v2Entry 9 }

		-- 1.3.6.1.4.1.10106.3.101291.1.1.11
		dli3000p01v2FadeTime OBJECT-TYPE
			SYNTAX DelayFram3
			MAX-ACCESS read-write
			STATUS current
			DESCRIPTION
				"Allows selecting a fade time for logo insertion"
		::= { dli3000p01v2Entry 11 }

		-- 1.3.6.1.4.1.10106.3.101291.1.1.13
		dli3000p01v2LogoPosH OBJECT-TYPE
			SYNTAX LogoPosH1
			MAX-ACCESS read-write
			STATUS current
			DESCRIPTION
				"Allows selecting the logo horizontal position"
		::= { dli3000p01v2Entry 13 }

		-- 1.3.6.1.4.1.10106.3.101291.1.1.15
		dli3000p01v2LogoSizeH OBJECT-TYPE
			SYNTAX LogoSizH1
			MAX-ACCESS read-write
			STATUS current
			DESCRIPTION
				"Allows selecting the logo horizontal size"
		::= { dli3000p01v2Entry 15 }

		-- 1.3.6.1.4.1.10106.3.101291.1.1.17
		dli3000p01v2LogoPosV OBJECT-TYPE
			SYNTAX LogoPosV1
			MAX-ACCESS read-write
			STATUS current
			DESCRIPTION
				"Allows selecting the logo vertical position"
		::= { dli3000p01v2Entry 17 }

		-- 1.3.6.1.4.1.10106.3.101291.1.1.19
		dli3000p01v2LogoSizeV OBJECT-TYPE
			SYNTAX LogoSizV1
			MAX-ACCESS read-write
			STATUS current
			DESCRIPTION
				"Allows selecting the logo vertical size"
		::= { dli3000p01v2Entry 19 }

		-- 1.3.6.1.4.1.10106.3.101291.1.1.21
		dli3000p01v2LogoMemSize OBJECT-TYPE
			SYNTAX LogoSizeKpix1
			MAX-ACCESS read-write
			STATUS current
			DESCRIPTION
				"Allows selecting the logos size"
		::= { dli3000p01v2Entry 21 }

		-- 1.3.6.1.4.1.10106.3.101291.1.1.23
		dli3000p01v2MaxEq OBJECT-TYPE
			SYNTAX BitFail
			MAX-ACCESS read-only
			STATUS current
			DESCRIPTION
				"Equalizer status"
		::= { dli3000p01v2Entry 23 }

		-- 1.3.6.1.4.1.10106.3.101291.1.1.25
		dli3000p01v2NoSig OBJECT-TYPE
			SYNTAX BitFail
			MAX-ACCESS read-only
			STATUS current
			DESCRIPTION
				"Indicates no signal fail"
		::= { dli3000p01v2Entry 25 }

		-- 1.3.6.1.4.1.10106.3.101291.1.1.26
		dli3000p01v2NoSigTrapEnable OBJECT-TYPE
			SYNTAX AlarmEnable
			MAX-ACCESS read-write
			STATUS current
			DESCRIPTION
				"Indicates no signal fail Trap Enable"
		::= { dli3000p01v2Entry 26 }

		-- 1.3.6.1.4.1.10106.3.133501
		tly3032p01v1 OBJECT IDENTIFIER ::= { albalaProducts 133501 }

		-- 1.3.6.1.4.1.10106.3.133501.1
		tly3032p01v1Table  OBJECT-TYPE
			SYNTAX SEQUENCE OF Tly3032p01v1Entry
			MAX-ACCESS not-accessible
			STATUS current
			DESCRIPTION
				"Module  TLY3032P01V1 Table"
			::= { tly3032p01v1 1 }

		-- 1.3.6.1.4.1.10106.3.133501.1.1
		tly3032p01v1Entry  OBJECT-TYPE
			SYNTAX Tly3032p01v1Entry
			MAX-ACCESS not-accessible
			STATUS current
			DESCRIPTION
				"Module TLY3032P01V1 Entry"
			INDEX { tly3032p01v1Index }
			::= { tly3032p01v1Table 1 }

			Tly3032p01v1Entry ::=
			SEQUENCE {
				tly3032p01v1Index
				ModuleIndex,
				tly3032p01v1Gpi1
				Bit0Ina1Act,
				tly3032p01v1Gpi1TrapEnable
				AlarmEnable,
				tly3032p01v1Gpi2
				Bit0Ina1Act,
				tly3032p01v1Gpi2TrapEnable
				AlarmEnable,
				tly3032p01v1Gpi3
				Bit0Ina1Act,
				tly3032p01v1Gpi3TrapEnable
				AlarmEnable,
				tly3032p01v1Gpi4
				Bit0Ina1Act,
				tly3032p01v1Gpi4TrapEnable
				AlarmEnable,
				tly3032p01v1Gpi5
				Bit0Ina1Act,
				tly3032p01v1Gpi5TrapEnable
				AlarmEnable,
				tly3032p01v1Gpi6
				Bit0Ina1Act,
				tly3032p01v1Gpi6TrapEnable
				AlarmEnable,
				tly3032p01v1Gpi7
				Bit0Ina1Act,
				tly3032p01v1Gpi7TrapEnable
				AlarmEnable,
				tly3032p01v1Gpi8
				Bit0Ina1Act,
				tly3032p01v1Gpi8TrapEnable
				AlarmEnable,
				tly3032p01v1Gpi9
				Bit0Ina1Act,
				tly3032p01v1Gpi9TrapEnable
				AlarmEnable,
				tly3032p01v1Gpi10
				Bit0Ina1Act,
				tly3032p01v1Gpi10TrapEnable
				AlarmEnable,
				tly3032p01v1Gpi11
				Bit0Ina1Act,
				tly3032p01v1Gpi11TrapEnable
				AlarmEnable,
				tly3032p01v1Gpi12
				Bit0Ina1Act,
				tly3032p01v1Gpi12TrapEnable
				AlarmEnable,
				tly3032p01v1Gpi13
				Bit0Ina1Act,
				tly3032p01v1Gpi13TrapEnable
				AlarmEnable,
				tly3032p01v1Gpi14
				Bit0Ina1Act,
				tly3032p01v1Gpi14TrapEnable
				AlarmEnable,
				tly3032p01v1Gpi15
				Bit0Ina1Act,
				tly3032p01v1Gpi15TrapEnable
				AlarmEnable,
				tly3032p01v1Gpi16
				Bit0Ina1Act,
				tly3032p01v1Gpi16TrapEnable
				AlarmEnable,
				tly3032p01v1Gpi17
				Bit0Ina1Act,
				tly3032p01v1Gpi17TrapEnable
				AlarmEnable,
				tly3032p01v1Gpi18
				Bit0Ina1Act,
				tly3032p01v1Gpi18TrapEnable
				AlarmEnable,
				tly3032p01v1Gpi19
				Bit0Ina1Act,
				tly3032p01v1Gpi19TrapEnable
				AlarmEnable,
				tly3032p01v1Gpi20
				Bit0Ina1Act,
				tly3032p01v1Gpi20TrapEnable
				AlarmEnable,
				tly3032p01v1Gpi21
				Bit0Ina1Act,
				tly3032p01v1Gpi21TrapEnable
				AlarmEnable,
				tly3032p01v1Gpi22
				Bit0Ina1Act,
				tly3032p01v1Gpi22TrapEnable
				AlarmEnable,
				tly3032p01v1Gpi23
				Bit0Ina1Act,
				tly3032p01v1Gpi23TrapEnable
				AlarmEnable,
				tly3032p01v1Gpi24
				Bit0Ina1Act,
				tly3032p01v1Gpi24TrapEnable
				AlarmEnable,
				tly3032p01v1Gpi25
				Bit0Ina1Act,
				tly3032p01v1Gpi25TrapEnable
				AlarmEnable,
				tly3032p01v1Gpi26
				Bit0Ina1Act,
				tly3032p01v1Gpi26TrapEnable
				AlarmEnable,
				tly3032p01v1Gpi27
				Bit0Ina1Act,
				tly3032p01v1Gpi27TrapEnable
				AlarmEnable,
				tly3032p01v1Gpi28
				Bit0Ina1Act,
				tly3032p01v1Gpi28TrapEnable
				AlarmEnable,
				tly3032p01v1Gpi29
				Bit0Ina1Act,
				tly3032p01v1Gpi29TrapEnable
				AlarmEnable,
				tly3032p01v1Gpi30
				Bit0Ina1Act,
				tly3032p01v1Gpi30TrapEnable
				AlarmEnable,
				tly3032p01v1Gpi31
				Bit0Ina1Act,
				tly3032p01v1Gpi31TrapEnable
				AlarmEnable,
				tly3032p01v1Gpi32
				Bit0Ina1Act,
				tly3032p01v1Gpi32TrapEnable
				AlarmEnable
			 }

		-- 1.3.6.1.4.1.10106.3.101291.1.1.1
		tly3032p01v1Index OBJECT-TYPE
			SYNTAX ModuleIndex
			MAX-ACCESS read-only
			STATUS current
			DESCRIPTION
				"Index of TLY3032P01V1 Table"
		::= { tly3032p01v1Entry 1 }

		-- 1.3.6.1.4.1.10106.3.101291.1.1.3
		tly3032p01v1Gpi1 OBJECT-TYPE
			SYNTAX Bit0Ina1Act
			MAX-ACCESS read-only
			STATUS current
			DESCRIPTION
				"GPI1 status"
		::= { tly3032p01v1Entry 3 }

		-- 1.3.6.1.4.1.10106.3.101291.1.1.4
		tly3032p01v1Gpi1TrapEnable OBJECT-TYPE
			SYNTAX AlarmEnable
			MAX-ACCESS read-write
			STATUS current
			DESCRIPTION
				"GPI1 status Trap Enable"
		::= { tly3032p01v1Entry 4 }

		-- 1.3.6.1.4.1.10106.3.101291.1.1.5
		tly3032p01v1Gpi2 OBJECT-TYPE
			SYNTAX Bit0Ina1Act
			MAX-ACCESS read-only
			STATUS current
			DESCRIPTION
				"GPI2 status"
		::= { tly3032p01v1Entry 5 }

		-- 1.3.6.1.4.1.10106.3.101291.1.1.6
		tly3032p01v1Gpi2TrapEnable OBJECT-TYPE
			SYNTAX AlarmEnable
			MAX-ACCESS read-write
			STATUS current
			DESCRIPTION
				"GPI2 status Trap Enable"
		::= { tly3032p01v1Entry 6 }

		-- 1.3.6.1.4.1.10106.3.101291.1.1.7
		tly3032p01v1Gpi3 OBJECT-TYPE
			SYNTAX Bit0Ina1Act
			MAX-ACCESS read-only
			STATUS current
			DESCRIPTION
				"GPI3 status"
		::= { tly3032p01v1Entry 7 }

		-- 1.3.6.1.4.1.10106.3.101291.1.1.8
		tly3032p01v1Gpi3TrapEnable OBJECT-TYPE
			SYNTAX AlarmEnable
			MAX-ACCESS read-write
			STATUS current
			DESCRIPTION
				"GPI3 status Trap Enable"
		::= { tly3032p01v1Entry 8 }

		-- 1.3.6.1.4.1.10106.3.101291.1.1.9
		tly3032p01v1Gpi4 OBJECT-TYPE
			SYNTAX Bit0Ina1Act
			MAX-ACCESS read-only
			STATUS current
			DESCRIPTION
				"GPI4 status"
		::= { tly3032p01v1Entry 9 }

		-- 1.3.6.1.4.1.10106.3.101291.1.1.10
		tly3032p01v1Gpi4TrapEnable OBJECT-TYPE
			SYNTAX AlarmEnable
			MAX-ACCESS read-write
			STATUS current
			DESCRIPTION
				"GPI4 status Trap Enable"
		::= { tly3032p01v1Entry 10 }

		-- 1.3.6.1.4.1.10106.3.101291.1.1.11
		tly3032p01v1Gpi5 OBJECT-TYPE
			SYNTAX Bit0Ina1Act
			MAX-ACCESS read-only
			STATUS current
			DESCRIPTION
				"GPI5 status"
		::= { tly3032p01v1Entry 11 }

		-- 1.3.6.1.4.1.10106.3.101291.1.1.12
		tly3032p01v1Gpi5TrapEnable OBJECT-TYPE
			SYNTAX AlarmEnable
			MAX-ACCESS read-write
			STATUS current
			DESCRIPTION
				"GPI5 status Trap Enable"
		::= { tly3032p01v1Entry 12 }

		-- 1.3.6.1.4.1.10106.3.101291.1.1.13
		tly3032p01v1Gpi6 OBJECT-TYPE
			SYNTAX Bit0Ina1Act
			MAX-ACCESS read-only
			STATUS current
			DESCRIPTION
				"GPI6 status"
		::= { tly3032p01v1Entry 13 }

		-- 1.3.6.1.4.1.10106.3.101291.1.1.14
		tly3032p01v1Gpi6TrapEnable OBJECT-TYPE
			SYNTAX AlarmEnable
			MAX-ACCESS read-write
			STATUS current
			DESCRIPTION
				"GPI6 status Trap Enable"
		::= { tly3032p01v1Entry 14 }

		-- 1.3.6.1.4.1.10106.3.101291.1.1.15
		tly3032p01v1Gpi7 OBJECT-TYPE
			SYNTAX Bit0Ina1Act
			MAX-ACCESS read-only
			STATUS current
			DESCRIPTION
				"GPI7 status"
		::= { tly3032p01v1Entry 15 }

		-- 1.3.6.1.4.1.10106.3.101291.1.1.16
		tly3032p01v1Gpi7TrapEnable OBJECT-TYPE
			SYNTAX AlarmEnable
			MAX-ACCESS read-write
			STATUS current
			DESCRIPTION
				"GPI7 status Trap Enable"
		::= { tly3032p01v1Entry 16 }

		-- 1.3.6.1.4.1.10106.3.101291.1.1.17
		tly3032p01v1Gpi8 OBJECT-TYPE
			SYNTAX Bit0Ina1Act
			MAX-ACCESS read-only
			STATUS current
			DESCRIPTION
				"GPI8 status"
		::= { tly3032p01v1Entry 17 }

		-- 1.3.6.1.4.1.10106.3.101291.1.1.18
		tly3032p01v1Gpi8TrapEnable OBJECT-TYPE
			SYNTAX AlarmEnable
			MAX-ACCESS read-write
			STATUS current
			DESCRIPTION
				"GPI8 status Trap Enable"
		::= { tly3032p01v1Entry 18 }

		-- 1.3.6.1.4.1.10106.3.101291.1.1.19
		tly3032p01v1Gpi9 OBJECT-TYPE
			SYNTAX Bit0Ina1Act
			MAX-ACCESS read-only
			STATUS current
			DESCRIPTION
				"GPI9 status"
		::= { tly3032p01v1Entry 19 }

		-- 1.3.6.1.4.1.10106.3.101291.1.1.20
		tly3032p01v1Gpi9TrapEnable OBJECT-TYPE
			SYNTAX AlarmEnable
			MAX-ACCESS read-write
			STATUS current
			DESCRIPTION
				"GPI9 status Trap Enable"
		::= { tly3032p01v1Entry 20 }

		-- 1.3.6.1.4.1.10106.3.101291.1.1.21
		tly3032p01v1Gpi10 OBJECT-TYPE
			SYNTAX Bit0Ina1Act
			MAX-ACCESS read-only
			STATUS current
			DESCRIPTION
				"GPI10 status"
		::= { tly3032p01v1Entry 21 }

		-- 1.3.6.1.4.1.10106.3.101291.1.1.22
		tly3032p01v1Gpi10TrapEnable OBJECT-TYPE
			SYNTAX AlarmEnable
			MAX-ACCESS read-write
			STATUS current
			DESCRIPTION
				"GPI10 status Trap Enable"
		::= { tly3032p01v1Entry 22 }

		-- 1.3.6.1.4.1.10106.3.101291.1.1.23
		tly3032p01v1Gpi11 OBJECT-TYPE
			SYNTAX Bit0Ina1Act
			MAX-ACCESS read-only
			STATUS current
			DESCRIPTION
				"GPI11 status"
		::= { tly3032p01v1Entry 23 }

		-- 1.3.6.1.4.1.10106.3.101291.1.1.24
		tly3032p01v1Gpi11TrapEnable OBJECT-TYPE
			SYNTAX AlarmEnable
			MAX-ACCESS read-write
			STATUS current
			DESCRIPTION
				"GPI11 status Trap Enable"
		::= { tly3032p01v1Entry 24 }

		-- 1.3.6.1.4.1.10106.3.101291.1.1.25
		tly3032p01v1Gpi12 OBJECT-TYPE
			SYNTAX Bit0Ina1Act
			MAX-ACCESS read-only
			STATUS current
			DESCRIPTION
				"GPI12 status"
		::= { tly3032p01v1Entry 25 }

		-- 1.3.6.1.4.1.10106.3.101291.1.1.26
		tly3032p01v1Gpi12TrapEnable OBJECT-TYPE
			SYNTAX AlarmEnable
			MAX-ACCESS read-write
			STATUS current
			DESCRIPTION
				"GPI12 status Trap Enable"
		::= { tly3032p01v1Entry 26 }

		-- 1.3.6.1.4.1.10106.3.101291.1.1.27
		tly3032p01v1Gpi13 OBJECT-TYPE
			SYNTAX Bit0Ina1Act
			MAX-ACCESS read-only
			STATUS current
			DESCRIPTION
				"GPI13 status"
		::= { tly3032p01v1Entry 27 }

		-- 1.3.6.1.4.1.10106.3.101291.1.1.28
		tly3032p01v1Gpi13TrapEnable OBJECT-TYPE
			SYNTAX AlarmEnable
			MAX-ACCESS read-write
			STATUS current
			DESCRIPTION
				"GPI13 status Trap Enable"
		::= { tly3032p01v1Entry 28 }

		-- 1.3.6.1.4.1.10106.3.101291.1.1.29
		tly3032p01v1Gpi14 OBJECT-TYPE
			SYNTAX Bit0Ina1Act
			MAX-ACCESS read-only
			STATUS current
			DESCRIPTION
				"GPI14 status"
		::= { tly3032p01v1Entry 29 }

		-- 1.3.6.1.4.1.10106.3.101291.1.1.30
		tly3032p01v1Gpi14TrapEnable OBJECT-TYPE
			SYNTAX AlarmEnable
			MAX-ACCESS read-write
			STATUS current
			DESCRIPTION
				"GPI14 status Trap Enable"
		::= { tly3032p01v1Entry 30 }

		-- 1.3.6.1.4.1.10106.3.101291.1.1.31
		tly3032p01v1Gpi15 OBJECT-TYPE
			SYNTAX Bit0Ina1Act
			MAX-ACCESS read-only
			STATUS current
			DESCRIPTION
				"GPI15 status"
		::= { tly3032p01v1Entry 31 }

		-- 1.3.6.1.4.1.10106.3.101291.1.1.32
		tly3032p01v1Gpi15TrapEnable OBJECT-TYPE
			SYNTAX AlarmEnable
			MAX-ACCESS read-write
			STATUS current
			DESCRIPTION
				"GPI15 status Trap Enable"
		::= { tly3032p01v1Entry 32 }

		-- 1.3.6.1.4.1.10106.3.101291.1.1.33
		tly3032p01v1Gpi16 OBJECT-TYPE
			SYNTAX Bit0Ina1Act
			MAX-ACCESS read-only
			STATUS current
			DESCRIPTION
				"GPI16 status"
		::= { tly3032p01v1Entry 33 }

		-- 1.3.6.1.4.1.10106.3.101291.1.1.34
		tly3032p01v1Gpi16TrapEnable OBJECT-TYPE
			SYNTAX AlarmEnable
			MAX-ACCESS read-write
			STATUS current
			DESCRIPTION
				"GPI16 status Trap Enable"
		::= { tly3032p01v1Entry 34 }

		-- 1.3.6.1.4.1.10106.3.101291.1.1.35
		tly3032p01v1Gpi17 OBJECT-TYPE
			SYNTAX Bit0Ina1Act
			MAX-ACCESS read-only
			STATUS current
			DESCRIPTION
				"GPI17 status"
		::= { tly3032p01v1Entry 35 }

		-- 1.3.6.1.4.1.10106.3.101291.1.1.36
		tly3032p01v1Gpi17TrapEnable OBJECT-TYPE
			SYNTAX AlarmEnable
			MAX-ACCESS read-write
			STATUS current
			DESCRIPTION
				"GPI17 status Trap Enable"
		::= { tly3032p01v1Entry 36 }

		-- 1.3.6.1.4.1.10106.3.101291.1.1.37
		tly3032p01v1Gpi18 OBJECT-TYPE
			SYNTAX Bit0Ina1Act
			MAX-ACCESS read-only
			STATUS current
			DESCRIPTION
				"GPI18 status"
		::= { tly3032p01v1Entry 37 }

		-- 1.3.6.1.4.1.10106.3.101291.1.1.38
		tly3032p01v1Gpi18TrapEnable OBJECT-TYPE
			SYNTAX AlarmEnable
			MAX-ACCESS read-write
			STATUS current
			DESCRIPTION
				"GPI18 status Trap Enable"
		::= { tly3032p01v1Entry 38 }

		-- 1.3.6.1.4.1.10106.3.101291.1.1.39
		tly3032p01v1Gpi19 OBJECT-TYPE
			SYNTAX Bit0Ina1Act
			MAX-ACCESS read-only
			STATUS current
			DESCRIPTION
				"GPI19 status"
		::= { tly3032p01v1Entry 39 }

		-- 1.3.6.1.4.1.10106.3.101291.1.1.40
		tly3032p01v1Gpi19TrapEnable OBJECT-TYPE
			SYNTAX AlarmEnable
			MAX-ACCESS read-write
			STATUS current
			DESCRIPTION
				"GPI19 status Trap Enable"
		::= { tly3032p01v1Entry 40 }

		-- 1.3.6.1.4.1.10106.3.101291.1.1.41
		tly3032p01v1Gpi20 OBJECT-TYPE
			SYNTAX Bit0Ina1Act
			MAX-ACCESS read-only
			STATUS current
			DESCRIPTION
				"GPI20 status"
		::= { tly3032p01v1Entry 41 }

		-- 1.3.6.1.4.1.10106.3.101291.1.1.42
		tly3032p01v1Gpi20TrapEnable OBJECT-TYPE
			SYNTAX AlarmEnable
			MAX-ACCESS read-write
			STATUS current
			DESCRIPTION
				"GPI20 status Trap Enable"
		::= { tly3032p01v1Entry 42 }

		-- 1.3.6.1.4.1.10106.3.101291.1.1.43
		tly3032p01v1Gpi21 OBJECT-TYPE
			SYNTAX Bit0Ina1Act
			MAX-ACCESS read-only
			STATUS current
			DESCRIPTION
				"GPI21 status"
		::= { tly3032p01v1Entry 43 }

		-- 1.3.6.1.4.1.10106.3.101291.1.1.44
		tly3032p01v1Gpi21TrapEnable OBJECT-TYPE
			SYNTAX AlarmEnable
			MAX-ACCESS read-write
			STATUS current
			DESCRIPTION
				"GPI21 status Trap Enable"
		::= { tly3032p01v1Entry 44 }

		-- 1.3.6.1.4.1.10106.3.101291.1.1.45
		tly3032p01v1Gpi22 OBJECT-TYPE
			SYNTAX Bit0Ina1Act
			MAX-ACCESS read-only
			STATUS current
			DESCRIPTION
				"GPI22 status"
		::= { tly3032p01v1Entry 45 }

		-- 1.3.6.1.4.1.10106.3.101291.1.1.46
		tly3032p01v1Gpi22TrapEnable OBJECT-TYPE
			SYNTAX AlarmEnable
			MAX-ACCESS read-write
			STATUS current
			DESCRIPTION
				"GPI22 status Trap Enable"
		::= { tly3032p01v1Entry 46 }

		-- 1.3.6.1.4.1.10106.3.101291.1.1.47
		tly3032p01v1Gpi23 OBJECT-TYPE
			SYNTAX Bit0Ina1Act
			MAX-ACCESS read-only
			STATUS current
			DESCRIPTION
				"GPI23 status"
		::= { tly3032p01v1Entry 47 }

		-- 1.3.6.1.4.1.10106.3.101291.1.1.48
		tly3032p01v1Gpi23TrapEnable OBJECT-TYPE
			SYNTAX AlarmEnable
			MAX-ACCESS read-write
			STATUS current
			DESCRIPTION
				"GPI23 status Trap Enable"
		::= { tly3032p01v1Entry 48 }

		-- 1.3.6.1.4.1.10106.3.101291.1.1.49
		tly3032p01v1Gpi24 OBJECT-TYPE
			SYNTAX Bit0Ina1Act
			MAX-ACCESS read-only
			STATUS current
			DESCRIPTION
				"GPI24 status"
		::= { tly3032p01v1Entry 49 }

		-- 1.3.6.1.4.1.10106.3.101291.1.1.50
		tly3032p01v1Gpi24TrapEnable OBJECT-TYPE
			SYNTAX AlarmEnable
			MAX-ACCESS read-write
			STATUS current
			DESCRIPTION
				"GPI24 status Trap Enable"
		::= { tly3032p01v1Entry 50 }

		-- 1.3.6.1.4.1.10106.3.101291.1.1.51
		tly3032p01v1Gpi25 OBJECT-TYPE
			SYNTAX Bit0Ina1Act
			MAX-ACCESS read-only
			STATUS current
			DESCRIPTION
				"GPI25 status"
		::= { tly3032p01v1Entry 51 }

		-- 1.3.6.1.4.1.10106.3.101291.1.1.52
		tly3032p01v1Gpi25TrapEnable OBJECT-TYPE
			SYNTAX AlarmEnable
			MAX-ACCESS read-write
			STATUS current
			DESCRIPTION
				"GPI25 status Trap Enable"
		::= { tly3032p01v1Entry 52 }

		-- 1.3.6.1.4.1.10106.3.101291.1.1.53
		tly3032p01v1Gpi26 OBJECT-TYPE
			SYNTAX Bit0Ina1Act
			MAX-ACCESS read-only
			STATUS current
			DESCRIPTION
				"GPI26 status"
		::= { tly3032p01v1Entry 53 }

		-- 1.3.6.1.4.1.10106.3.101291.1.1.54
		tly3032p01v1Gpi26TrapEnable OBJECT-TYPE
			SYNTAX AlarmEnable
			MAX-ACCESS read-write
			STATUS current
			DESCRIPTION
				"GPI26 status Trap Enable"
		::= { tly3032p01v1Entry 54 }

		-- 1.3.6.1.4.1.10106.3.101291.1.1.55
		tly3032p01v1Gpi27 OBJECT-TYPE
			SYNTAX Bit0Ina1Act
			MAX-ACCESS read-only
			STATUS current
			DESCRIPTION
				"GPI27 status"
		::= { tly3032p01v1Entry 55 }

		-- 1.3.6.1.4.1.10106.3.101291.1.1.56
		tly3032p01v1Gpi27TrapEnable OBJECT-TYPE
			SYNTAX AlarmEnable
			MAX-ACCESS read-write
			STATUS current
			DESCRIPTION
				"GPI27 status Trap Enable"
		::= { tly3032p01v1Entry 56 }

		-- 1.3.6.1.4.1.10106.3.101291.1.1.57
		tly3032p01v1Gpi28 OBJECT-TYPE
			SYNTAX Bit0Ina1Act
			MAX-ACCESS read-only
			STATUS current
			DESCRIPTION
				"GPI28 status"
		::= { tly3032p01v1Entry 57 }

		-- 1.3.6.1.4.1.10106.3.101291.1.1.58
		tly3032p01v1Gpi28TrapEnable OBJECT-TYPE
			SYNTAX AlarmEnable
			MAX-ACCESS read-write
			STATUS current
			DESCRIPTION
				"GPI28 status Trap Enable"
		::= { tly3032p01v1Entry 58 }

		-- 1.3.6.1.4.1.10106.3.101291.1.1.59
		tly3032p01v1Gpi29 OBJECT-TYPE
			SYNTAX Bit0Ina1Act
			MAX-ACCESS read-only
			STATUS current
			DESCRIPTION
				"GPI29 status"
		::= { tly3032p01v1Entry 59 }

		-- 1.3.6.1.4.1.10106.3.101291.1.1.60
		tly3032p01v1Gpi29TrapEnable OBJECT-TYPE
			SYNTAX AlarmEnable
			MAX-ACCESS read-write
			STATUS current
			DESCRIPTION
				"GPI29 status Trap Enable"
		::= { tly3032p01v1Entry 60 }

		-- 1.3.6.1.4.1.10106.3.101291.1.1.61
		tly3032p01v1Gpi30 OBJECT-TYPE
			SYNTAX Bit0Ina1Act
			MAX-ACCESS read-only
			STATUS current
			DESCRIPTION
				"GPI30 status"
		::= { tly3032p01v1Entry 61 }

		-- 1.3.6.1.4.1.10106.3.101291.1.1.62
		tly3032p01v1Gpi30TrapEnable OBJECT-TYPE
			SYNTAX AlarmEnable
			MAX-ACCESS read-write
			STATUS current
			DESCRIPTION
				"GPI30 status Trap Enable"
		::= { tly3032p01v1Entry 62 }

		-- 1.3.6.1.4.1.10106.3.101291.1.1.63
		tly3032p01v1Gpi31 OBJECT-TYPE
			SYNTAX Bit0Ina1Act
			MAX-ACCESS read-only
			STATUS current
			DESCRIPTION
				"GPI31 status"
		::= { tly3032p01v1Entry 63 }

		-- 1.3.6.1.4.1.10106.3.101291.1.1.64
		tly3032p01v1Gpi31TrapEnable OBJECT-TYPE
			SYNTAX AlarmEnable
			MAX-ACCESS read-write
			STATUS current
			DESCRIPTION
				"GPI31 status Trap Enable"
		::= { tly3032p01v1Entry 64 }

		-- 1.3.6.1.4.1.10106.3.101291.1.1.65
		tly3032p01v1Gpi32 OBJECT-TYPE
			SYNTAX Bit0Ina1Act
			MAX-ACCESS read-only
			STATUS current
			DESCRIPTION
				"GPI32 status"
		::= { tly3032p01v1Entry 65 }

		-- 1.3.6.1.4.1.10106.3.101291.1.1.66
		tly3032p01v1Gpi32TrapEnable OBJECT-TYPE
			SYNTAX AlarmEnable
			MAX-ACCESS read-write
			STATUS current
			DESCRIPTION
				"GPI32 status Trap Enable"
		::= { tly3032p01v1Entry 66 }

		-- 1.3.6.1.4.1.10106.3.133901
		tly3016p01v1 OBJECT IDENTIFIER ::= { albalaProducts 133901 }

		-- 1.3.6.1.4.1.10106.3.133901.1
		tly3016p01v1Table  OBJECT-TYPE
			SYNTAX SEQUENCE OF Tly3016p01v1Entry
			MAX-ACCESS not-accessible
			STATUS current
			DESCRIPTION
				"Module  TLY3016P01V1 Table"
			::= { tly3016p01v1 1 }

		-- 1.3.6.1.4.1.10106.3.133901.1.1
		tly3016p01v1Entry  OBJECT-TYPE
			SYNTAX Tly3016p01v1Entry
			MAX-ACCESS not-accessible
			STATUS current
			DESCRIPTION
				"Module TLY3016P01V1 Entry"
			INDEX { tly3016p01v1Index }
			::= { tly3016p01v1Table 1 }

			Tly3016p01v1Entry ::=
			SEQUENCE {
				tly3016p01v1Index
				ModuleIndex,
				tly3016p01v1Gpo1
				Bit0Ina1Act,
				tly3016p01v1Gpo2
				Bit0Ina1Act,
				tly3016p01v1Gpo3
				Bit0Ina1Act,
				tly3016p01v1Gpo4
				Bit0Ina1Act,
				tly3016p01v1Gpo5
				Bit0Ina1Act,
				tly3016p01v1Gpo6
				Bit0Ina1Act,
				tly3016p01v1Gpo7
				Bit0Ina1Act,
				tly3016p01v1Gpo8
				Bit0Ina1Act,
				tly3016p01v1Gpo9
				Bit0Ina1Act,
				tly3016p01v1Gpo10
				Bit0Ina1Act,
				tly3016p01v1Gpo11
				Bit0Ina1Act,
				tly3016p01v1Gpo12
				Bit0Ina1Act,
				tly3016p01v1Gpo13
				Bit0Ina1Act,
				tly3016p01v1Gpo14
				Bit0Ina1Act,
				tly3016p01v1Gpo15
				Bit0Ina1Act,
				tly3016p01v1Gpo16
				Bit0Ina1Act
			 }

		-- 1.3.6.1.4.1.10106.3.101291.1.1.1
		tly3016p01v1Index OBJECT-TYPE
			SYNTAX ModuleIndex
			MAX-ACCESS read-only
			STATUS current
			DESCRIPTION
				"Index of TLY3016P01V1 Table"
		::= { tly3016p01v1Entry 1 }

		-- 1.3.6.1.4.1.10106.3.101291.1.1.3
		tly3016p01v1Gpo1 OBJECT-TYPE
			SYNTAX Bit0Ina1Act
			MAX-ACCESS read-write
			STATUS current
			DESCRIPTION
				"Allows control of GPO1"
		::= { tly3016p01v1Entry 3 }

		-- 1.3.6.1.4.1.10106.3.101291.1.1.5
		tly3016p01v1Gpo2 OBJECT-TYPE
			SYNTAX Bit0Ina1Act
			MAX-ACCESS read-write
			STATUS current
			DESCRIPTION
				"Allows control of GPO2"
		::= { tly3016p01v1Entry 5 }

		-- 1.3.6.1.4.1.10106.3.101291.1.1.7
		tly3016p01v1Gpo3 OBJECT-TYPE
			SYNTAX Bit0Ina1Act
			MAX-ACCESS read-write
			STATUS current
			DESCRIPTION
				"Allows control of GPO3"
		::= { tly3016p01v1Entry 7 }

		-- 1.3.6.1.4.1.10106.3.101291.1.1.9
		tly3016p01v1Gpo4 OBJECT-TYPE
			SYNTAX Bit0Ina1Act
			MAX-ACCESS read-write
			STATUS current
			DESCRIPTION
				"Allows control of GPO4"
		::= { tly3016p01v1Entry 9 }

		-- 1.3.6.1.4.1.10106.3.101291.1.1.11
		tly3016p01v1Gpo5 OBJECT-TYPE
			SYNTAX Bit0Ina1Act
			MAX-ACCESS read-write
			STATUS current
			DESCRIPTION
				"Allows control of GPO5"
		::= { tly3016p01v1Entry 11 }

		-- 1.3.6.1.4.1.10106.3.101291.1.1.13
		tly3016p01v1Gpo6 OBJECT-TYPE
			SYNTAX Bit0Ina1Act
			MAX-ACCESS read-write
			STATUS current
			DESCRIPTION
				"Allows control of GPO6"
		::= { tly3016p01v1Entry 13 }

		-- 1.3.6.1.4.1.10106.3.101291.1.1.15
		tly3016p01v1Gpo7 OBJECT-TYPE
			SYNTAX Bit0Ina1Act
			MAX-ACCESS read-write
			STATUS current
			DESCRIPTION
				"Allows control of GPO7"
		::= { tly3016p01v1Entry 15 }

		-- 1.3.6.1.4.1.10106.3.101291.1.1.17
		tly3016p01v1Gpo8 OBJECT-TYPE
			SYNTAX Bit0Ina1Act
			MAX-ACCESS read-write
			STATUS current
			DESCRIPTION
				"Allows control of GPO8"
		::= { tly3016p01v1Entry 17 }

		-- 1.3.6.1.4.1.10106.3.101291.1.1.19
		tly3016p01v1Gpo9 OBJECT-TYPE
			SYNTAX Bit0Ina1Act
			MAX-ACCESS read-write
			STATUS current
			DESCRIPTION
				"Allows control of GPO9"
		::= { tly3016p01v1Entry 19 }

		-- 1.3.6.1.4.1.10106.3.101291.1.1.21
		tly3016p01v1Gpo10 OBJECT-TYPE
			SYNTAX Bit0Ina1Act
			MAX-ACCESS read-write
			STATUS current
			DESCRIPTION
				"Allows control of GPO10"
		::= { tly3016p01v1Entry 21 }

		-- 1.3.6.1.4.1.10106.3.101291.1.1.23
		tly3016p01v1Gpo11 OBJECT-TYPE
			SYNTAX Bit0Ina1Act
			MAX-ACCESS read-write
			STATUS current
			DESCRIPTION
				"Allows control of GPO11"
		::= { tly3016p01v1Entry 23 }

		-- 1.3.6.1.4.1.10106.3.101291.1.1.25
		tly3016p01v1Gpo12 OBJECT-TYPE
			SYNTAX Bit0Ina1Act
			MAX-ACCESS read-write
			STATUS current
			DESCRIPTION
				"Allows control of GPO12"
		::= { tly3016p01v1Entry 25 }

		-- 1.3.6.1.4.1.10106.3.101291.1.1.27
		tly3016p01v1Gpo13 OBJECT-TYPE
			SYNTAX Bit0Ina1Act
			MAX-ACCESS read-write
			STATUS current
			DESCRIPTION
				"Allows control of GPO13"
		::= { tly3016p01v1Entry 27 }

		-- 1.3.6.1.4.1.10106.3.101291.1.1.29
		tly3016p01v1Gpo14 OBJECT-TYPE
			SYNTAX Bit0Ina1Act
			MAX-ACCESS read-write
			STATUS current
			DESCRIPTION
				"Allows control of GPO14"
		::= { tly3016p01v1Entry 29 }

		-- 1.3.6.1.4.1.10106.3.101291.1.1.31
		tly3016p01v1Gpo15 OBJECT-TYPE
			SYNTAX Bit0Ina1Act
			MAX-ACCESS read-write
			STATUS current
			DESCRIPTION
				"Allows control of GPO15"
		::= { tly3016p01v1Entry 31 }

		-- 1.3.6.1.4.1.10106.3.101291.1.1.33
		tly3016p01v1Gpo16 OBJECT-TYPE
			SYNTAX Bit0Ina1Act
			MAX-ACCESS read-write
			STATUS current
			DESCRIPTION
				"Allows control of GPO16"
		::= { tly3016p01v1Entry 33 }

		-- 1.3.6.1.4.1.10106.3.134801
		aac3000p01v1 OBJECT IDENTIFIER ::= { albalaProducts 134801 }

		-- 1.3.6.1.4.1.10106.3.134801.1
		aac3000p01v1Table  OBJECT-TYPE
			SYNTAX SEQUENCE OF Aac3000p01v1Entry
			MAX-ACCESS not-accessible
			STATUS current
			DESCRIPTION
				"Module  AAC3000P01V1 Table"
			::= { aac3000p01v1 1 }

		-- 1.3.6.1.4.1.10106.3.134801.1.1
		aac3000p01v1Entry  OBJECT-TYPE
			SYNTAX Aac3000p01v1Entry
			MAX-ACCESS not-accessible
			STATUS current
			DESCRIPTION
				"Module AAC3000P01V1 Entry"
			INDEX { aac3000p01v1Index }
			::= { aac3000p01v1Table 1 }

			Aac3000p01v1Entry ::=
			SEQUENCE {
				aac3000p01v1Index
				ModuleIndex,
				aac3000p01v1Bits
				Bit024120,
				aac3000p01v1Silence
				Bit0Ena1Dis,
				aac3000p01v1Mode
				Bit0Man1Aut,
				aac3000p01v1InputRef
				AudioRef3,
				aac3000p01v1OutputFreq
				AudioSelFreq5,
				aac3000p01v1OvlLevel
				Uint8,
				aac3000p01v1NoVid
				BitFail,
				aac3000p01v1NoVidTrapEnable
				AlarmEnable,
				aac3000p01v1NoAes
				BitFail,
				aac3000p01v1NoAesTrapEnable
				AlarmEnable,
				aac3000p01v1NoWclk
				BitFail,
				aac3000p01v1NoWclkTrapEnable
				AlarmEnable,
				aac3000p01v1Unlock
				BitFail,
				aac3000p01v1UnlockTrapEnable
				AlarmEnable,
				aac3000p01v1OvldS1Cha
				BitFail,
				aac3000p01v1OvldS1ChaTrapEnable
				AlarmEnable,
				aac3000p01v1OvldS1Chb
				BitFail,
				aac3000p01v1OvldS1ChbTrapEnable
				AlarmEnable,
				aac3000p01v1OvldS2Cha
				BitFail,
				aac3000p01v1OvldS2ChaTrapEnable
				AlarmEnable,
				aac3000p01v1OvldS2Chb
				BitFail,
				aac3000p01v1OvldS2ChbTrapEnable
				AlarmEnable,
				aac3000p01v1AesDetFreq
				AudioSelFreq6,
				aac3000p01v1WclkDetFreq
				AudioSelFreq6,
				aac3000p01v1Det525
				Bit0No1Yes,
				aac3000p01v1Det625
				Bit0No1Yes
			 }

		-- 1.3.6.1.4.1.10106.3.101291.1.1.1
		aac3000p01v1Index OBJECT-TYPE
			SYNTAX ModuleIndex
			MAX-ACCESS read-only
			STATUS current
			DESCRIPTION
				"Index of AAC3000P01V1 Table"
		::= { aac3000p01v1Entry 1 }

		-- 1.3.6.1.4.1.10106.3.101291.1.1.3
		aac3000p01v1Bits OBJECT-TYPE
			SYNTAX Bit024120
			MAX-ACCESS read-only
			STATUS current
			DESCRIPTION
				"Allows selecting the number of bits"
		::= { aac3000p01v1Entry 3 }

		-- 1.3.6.1.4.1.10106.3.101291.1.1.5
		aac3000p01v1Silence OBJECT-TYPE
			SYNTAX Bit0Ena1Dis
			MAX-ACCESS read-only
			STATUS current
			DESCRIPTION
				"Allows silencing the output"
		::= { aac3000p01v1Entry 5 }

		-- 1.3.6.1.4.1.10106.3.101291.1.1.7
		aac3000p01v1Mode OBJECT-TYPE
			SYNTAX Bit0Man1Aut
			MAX-ACCESS read-only
			STATUS current
			DESCRIPTION
				"Allows selecting the reference selection mode"
		::= { aac3000p01v1Entry 7 }

		-- 1.3.6.1.4.1.10106.3.101291.1.1.9
		aac3000p01v1InputRef OBJECT-TYPE
			SYNTAX AudioRef3
			MAX-ACCESS read-only
			STATUS current
			DESCRIPTION
				"Allows selecting the reference input in manual mode"
		::= { aac3000p01v1Entry 9 }

		-- 1.3.6.1.4.1.10106.3.101291.1.1.11
		aac3000p01v1OutputFreq OBJECT-TYPE
			SYNTAX AudioSelFreq5
			MAX-ACCESS read-only
			STATUS current
			DESCRIPTION
				"Allows selecting the output samplign frequency in manual mode"
		::= { aac3000p01v1Entry 11 }

		-- 1.3.6.1.4.1.10106.3.101291.1.1.13
		aac3000p01v1OvlLevel OBJECT-TYPE
			SYNTAX Uint8
			MAX-ACCESS read-write
			STATUS current
			DESCRIPTION
				"Allows selecting the overload indicator threshold level"
		::= { aac3000p01v1Entry 13 }

		-- 1.3.6.1.4.1.10106.3.101291.1.1.15
		aac3000p01v1NoVid OBJECT-TYPE
			SYNTAX BitFail
			MAX-ACCESS read-only
			STATUS current
			DESCRIPTION
				"Indicates no video reference signal"
		::= { aac3000p01v1Entry 15 }

		-- 1.3.6.1.4.1.10106.3.101291.1.1.16
		aac3000p01v1NoVidTrapEnable OBJECT-TYPE
			SYNTAX AlarmEnable
			MAX-ACCESS read-write
			STATUS current
			DESCRIPTION
				"Indicates no video reference signal Trap Enable"
		::= { aac3000p01v1Entry 16 }

		-- 1.3.6.1.4.1.10106.3.101291.1.1.17
		aac3000p01v1NoAes OBJECT-TYPE
			SYNTAX BitFail
			MAX-ACCESS read-only
			STATUS current
			DESCRIPTION
				"Indicates no AES reference signal"
		::= { aac3000p01v1Entry 17 }

		-- 1.3.6.1.4.1.10106.3.101291.1.1.18
		aac3000p01v1NoAesTrapEnable OBJECT-TYPE
			SYNTAX AlarmEnable
			MAX-ACCESS read-write
			STATUS current
			DESCRIPTION
				"Indicates no AES reference signal Trap Enable"
		::= { aac3000p01v1Entry 18 }

		-- 1.3.6.1.4.1.10106.3.101291.1.1.19
		aac3000p01v1NoWclk OBJECT-TYPE
			SYNTAX BitFail
			MAX-ACCESS read-only
			STATUS current
			DESCRIPTION
				"Indicates no Wordclock reference signal"
		::= { aac3000p01v1Entry 19 }

		-- 1.3.6.1.4.1.10106.3.101291.1.1.20
		aac3000p01v1NoWclkTrapEnable OBJECT-TYPE
			SYNTAX AlarmEnable
			MAX-ACCESS read-write
			STATUS current
			DESCRIPTION
				"Indicates no Wordclock reference signal Trap Enable"
		::= { aac3000p01v1Entry 20 }

		-- 1.3.6.1.4.1.10106.3.101291.1.1.21
		aac3000p01v1Unlock OBJECT-TYPE
			SYNTAX BitFail
			MAX-ACCESS read-only
			STATUS current
			DESCRIPTION
				"Indicates AES reference unlock fail"
		::= { aac3000p01v1Entry 21 }

		-- 1.3.6.1.4.1.10106.3.101291.1.1.22
		aac3000p01v1UnlockTrapEnable OBJECT-TYPE
			SYNTAX AlarmEnable
			MAX-ACCESS read-write
			STATUS current
			DESCRIPTION
				"Indicates AES reference unlock fail Trap Enable"
		::= { aac3000p01v1Entry 22 }

		-- 1.3.6.1.4.1.10106.3.101291.1.1.23
		aac3000p01v1OvldS1Cha OBJECT-TYPE
			SYNTAX BitFail
			MAX-ACCESS read-only
			STATUS current
			DESCRIPTION
				"Indicates streaml 1 channel A overload fail"
		::= { aac3000p01v1Entry 23 }

		-- 1.3.6.1.4.1.10106.3.101291.1.1.24
		aac3000p01v1OvldS1ChaTrapEnable OBJECT-TYPE
			SYNTAX AlarmEnable
			MAX-ACCESS read-write
			STATUS current
			DESCRIPTION
				"Indicates streaml 1 channel A overload fail Trap Enable"
		::= { aac3000p01v1Entry 24 }

		-- 1.3.6.1.4.1.10106.3.101291.1.1.25
		aac3000p01v1OvldS1Chb OBJECT-TYPE
			SYNTAX BitFail
			MAX-ACCESS read-only
			STATUS current
			DESCRIPTION
				"Indicates streaml 1 channel B overload fail"
		::= { aac3000p01v1Entry 25 }

		-- 1.3.6.1.4.1.10106.3.101291.1.1.26
		aac3000p01v1OvldS1ChbTrapEnable OBJECT-TYPE
			SYNTAX AlarmEnable
			MAX-ACCESS read-write
			STATUS current
			DESCRIPTION
				"Indicates streaml 1 channel B overload fail Trap Enable"
		::= { aac3000p01v1Entry 26 }

		-- 1.3.6.1.4.1.10106.3.101291.1.1.27
		aac3000p01v1OvldS2Cha OBJECT-TYPE
			SYNTAX BitFail
			MAX-ACCESS read-only
			STATUS current
			DESCRIPTION
				"Indicates streaml 2 channel A overload fail"
		::= { aac3000p01v1Entry 27 }

		-- 1.3.6.1.4.1.10106.3.101291.1.1.28
		aac3000p01v1OvldS2ChaTrapEnable OBJECT-TYPE
			SYNTAX AlarmEnable
			MAX-ACCESS read-write
			STATUS current
			DESCRIPTION
				"Indicates streaml 2 channel A overload fail Trap Enable"
		::= { aac3000p01v1Entry 28 }

		-- 1.3.6.1.4.1.10106.3.101291.1.1.29
		aac3000p01v1OvldS2Chb OBJECT-TYPE
			SYNTAX BitFail
			MAX-ACCESS read-only
			STATUS current
			DESCRIPTION
				"Indicates streaml 2 channel B overload fail"
		::= { aac3000p01v1Entry 29 }

		-- 1.3.6.1.4.1.10106.3.101291.1.1.30
		aac3000p01v1OvldS2ChbTrapEnable OBJECT-TYPE
			SYNTAX AlarmEnable
			MAX-ACCESS read-write
			STATUS current
			DESCRIPTION
				"Indicates streaml 2 channel B overload fail Trap Enable"
		::= { aac3000p01v1Entry 30 }

		-- 1.3.6.1.4.1.10106.3.101291.1.1.31
		aac3000p01v1AesDetFreq OBJECT-TYPE
			SYNTAX AudioSelFreq6
			MAX-ACCESS read-only
			STATUS current
			DESCRIPTION
				"Indicates the AES reference detected frequency"
		::= { aac3000p01v1Entry 31 }

		-- 1.3.6.1.4.1.10106.3.101291.1.1.33
		aac3000p01v1WclkDetFreq OBJECT-TYPE
			SYNTAX AudioSelFreq6
			MAX-ACCESS read-only
			STATUS current
			DESCRIPTION
				"Indicates tje Wordclock reference detected frequency"
		::= { aac3000p01v1Entry 33 }

		-- 1.3.6.1.4.1.10106.3.101291.1.1.35
		aac3000p01v1Det525 OBJECT-TYPE
			SYNTAX Bit0No1Yes
			MAX-ACCESS read-only
			STATUS current
			DESCRIPTION
				"525 lines signal detected"
		::= { aac3000p01v1Entry 35 }

		-- 1.3.6.1.4.1.10106.3.101291.1.1.37
		aac3000p01v1Det625 OBJECT-TYPE
			SYNTAX Bit0No1Yes
			MAX-ACCESS read-only
			STATUS current
			DESCRIPTION
				"625 lines signal detected"
		::= { aac3000p01v1Entry 37 }

		-- 1.3.6.1.4.1.10106.3.134901
		aem3000p01v1 OBJECT IDENTIFIER ::= { albalaProducts 134901 }

		-- 1.3.6.1.4.1.10106.3.134901.1
		aem3000p01v1Table  OBJECT-TYPE
			SYNTAX SEQUENCE OF Aem3000p01v1Entry
			MAX-ACCESS not-accessible
			STATUS current
			DESCRIPTION
				"Module  AEM3000P01V1 Table"
			::= { aem3000p01v1 1 }

		-- 1.3.6.1.4.1.10106.3.134901.1.1
		aem3000p01v1Entry  OBJECT-TYPE
			SYNTAX Aem3000p01v1Entry
			MAX-ACCESS not-accessible
			STATUS current
			DESCRIPTION
				"Module AEM3000P01V1 Entry"
			INDEX { aem3000p01v1Index }
			::= { aem3000p01v1Table 1 }

			Aem3000p01v1Entry ::=
			SEQUENCE {
				aem3000p01v1Index
				ModuleIndex,
				aem3000p01v1EmbedIns
				Bit0No1Yes,
				aem3000p01v1EmbedMode
				Bit0Clr1App,
				aem3000p01v1EmbedCh
				Bit0214,
				aem3000p01v1EmbedBits
				Bit024120,
				aem3000p01v1Group
				EmbedGroup,
				aem3000p01v1GroupTrapEnable
				AlarmEnable,
				aem3000p01v1GainAes1A
				Gain24dbMute,
				aem3000p01v1PhaseAes1A
				Bit0Nor1Inv,
				aem3000p01v1GainAes1B
				Gain24dbMute,
				aem3000p01v1PhaseAes1B
				Bit0Nor1Inv,
				aem3000p01v1GainAes2A
				Gain24dbMute,
				aem3000p01v1PhaseAes2A
				Bit0Nor1Inv,
				aem3000p01v1GainAes2B
				Gain24dbMute,
				aem3000p01v1PhaseAes2B
				Bit0Nor1Inv,
				aem3000p01v1Aes1AInput
				AnaMxInput1,
				aem3000p01v1Aes1BInput
				AnaMxInput1,
				aem3000p01v1Aes2AInput
				AnaMxInput1,
				aem3000p01v1Aes2BInput
				AnaMxInput1,
				aem3000p01v1OverloadLevel
				LevelDbfs2,
				aem3000p01v1SilenceLevel
				LevelDbfs2,
				aem3000p01v1SilenceTime
				TimeS3,
				aem3000p01v1NoSignal
				BitFail,
				aem3000p01v1NoSignalTrapEnable
				AlarmEnable,
				aem3000p01v1SilOut1
				BitFail,
				aem3000p01v1SilOut1TrapEnable
				AlarmEnable,
				aem3000p01v1SilOut2
				BitFail,
				aem3000p01v1SilOut2TrapEnable
				AlarmEnable,
				aem3000p01v1OvlOut1
				BitFail,
				aem3000p01v1OvlOut1TrapEnable
				AlarmEnable,
				aem3000p01v1OvlOut2
				BitFail,
				aem3000p01v1OvlOut2TrapEnable
				AlarmEnable,
				aem3000p01v1PckAGr1
				Bit0No1Yes,
				aem3000p01v1PckAGr2
				Bit0No1Yes,
				aem3000p01v1PckAGr3
				Bit0No1Yes,
				aem3000p01v1PckAGr4
				Bit0No1Yes
			 }

		-- 1.3.6.1.4.1.10106.3.101291.1.1.1
		aem3000p01v1Index OBJECT-TYPE
			SYNTAX ModuleIndex
			MAX-ACCESS read-only
			STATUS current
			DESCRIPTION
				"Index of AEM3000P01V1 Table"
		::= { aem3000p01v1Entry 1 }

		-- 1.3.6.1.4.1.10106.3.101291.1.1.3
		aem3000p01v1EmbedIns OBJECT-TYPE
			SYNTAX Bit0No1Yes
			MAX-ACCESS read-write
			STATUS current
			DESCRIPTION
				"Allows selecting if the audio is embedded"
		::= { aem3000p01v1Entry 3 }

		-- 1.3.6.1.4.1.10106.3.101291.1.1.5
		aem3000p01v1EmbedMode OBJECT-TYPE
			SYNTAX Bit0Clr1App
			MAX-ACCESS read-write
			STATUS current
			DESCRIPTION
				"Allows selecting if the incoming audio groups are deleted before embedding"
		::= { aem3000p01v1Entry 5 }

		-- 1.3.6.1.4.1.10106.3.101291.1.1.7
		aem3000p01v1EmbedCh OBJECT-TYPE
			SYNTAX Bit0214
			MAX-ACCESS read-write
			STATUS current
			DESCRIPTION
				"Allows selecting the number of AES frames embedded in the group"
		::= { aem3000p01v1Entry 7 }

		-- 1.3.6.1.4.1.10106.3.101291.1.1.9
		aem3000p01v1EmbedBits OBJECT-TYPE
			SYNTAX Bit024120
			MAX-ACCESS read-write
			STATUS current
			DESCRIPTION
				"Allows selecting the number of bits of the embedded audio"
		::= { aem3000p01v1Entry 9 }

		-- 1.3.6.1.4.1.10106.3.101291.1.1.11
		aem3000p01v1Group OBJECT-TYPE
			SYNTAX EmbedGroup
			MAX-ACCESS read-write
			STATUS current
			DESCRIPTION
				"Allows selecting the group in which the audio is embedded"
		::= { aem3000p01v1Entry 11 }

		-- 1.3.6.1.4.1.10106.3.101291.1.1.12
		aem3000p01v1GroupTrapEnable OBJECT-TYPE
			SYNTAX AlarmEnable
			MAX-ACCESS read-write
			STATUS current
			DESCRIPTION
				"Allows selecting the group in which the audio is embedded Trap Enable"
		::= { aem3000p01v1Entry 12 }

		-- 1.3.6.1.4.1.10106.3.101291.1.1.13
		aem3000p01v1GainAes1A OBJECT-TYPE
			SYNTAX Gain24dbMute
			MAX-ACCESS read-write
			STATUS current
			DESCRIPTION
				"Allows adjusting the gain of AES1 channel A"
		::= { aem3000p01v1Entry 13 }

		-- 1.3.6.1.4.1.10106.3.101291.1.1.15
		aem3000p01v1PhaseAes1A OBJECT-TYPE
			SYNTAX Bit0Nor1Inv
			MAX-ACCESS read-write
			STATUS current
			DESCRIPTION
				"Allows changing the phase of AES1 channel A"
		::= { aem3000p01v1Entry 15 }

		-- 1.3.6.1.4.1.10106.3.101291.1.1.17
		aem3000p01v1GainAes1B OBJECT-TYPE
			SYNTAX Gain24dbMute
			MAX-ACCESS read-write
			STATUS current
			DESCRIPTION
				"Allows adjusting the gain of AES1 channel B"
		::= { aem3000p01v1Entry 17 }

		-- 1.3.6.1.4.1.10106.3.101291.1.1.19
		aem3000p01v1PhaseAes1B OBJECT-TYPE
			SYNTAX Bit0Nor1Inv
			MAX-ACCESS read-write
			STATUS current
			DESCRIPTION
				"Allows changing the phase of AES1 channel B"
		::= { aem3000p01v1Entry 19 }

		-- 1.3.6.1.4.1.10106.3.101291.1.1.21
		aem3000p01v1GainAes2A OBJECT-TYPE
			SYNTAX Gain24dbMute
			MAX-ACCESS read-write
			STATUS current
			DESCRIPTION
				"Allows adjusting the gain of AES2 channel A"
		::= { aem3000p01v1Entry 21 }

		-- 1.3.6.1.4.1.10106.3.101291.1.1.23
		aem3000p01v1PhaseAes2A OBJECT-TYPE
			SYNTAX Bit0Nor1Inv
			MAX-ACCESS read-write
			STATUS current
			DESCRIPTION
				"Allows changing the phase of AES2 channel A"
		::= { aem3000p01v1Entry 23 }

		-- 1.3.6.1.4.1.10106.3.101291.1.1.25
		aem3000p01v1GainAes2B OBJECT-TYPE
			SYNTAX Gain24dbMute
			MAX-ACCESS read-write
			STATUS current
			DESCRIPTION
				"Allows adjusting the gain of AES2 channel B"
		::= { aem3000p01v1Entry 25 }

		-- 1.3.6.1.4.1.10106.3.101291.1.1.27
		aem3000p01v1PhaseAes2B OBJECT-TYPE
			SYNTAX Bit0Nor1Inv
			MAX-ACCESS read-write
			STATUS current
			DESCRIPTION
				"Allows changing the phase of AES2 channel B"
		::= { aem3000p01v1Entry 27 }

		-- 1.3.6.1.4.1.10106.3.101291.1.1.29
		aem3000p01v1Aes1AInput OBJECT-TYPE
			SYNTAX AnaMxInput1
			MAX-ACCESS read-write
			STATUS current
			DESCRIPTION
				"Allows selecting the embedded SDI audio channel that is routed to AES1 channel A"
		::= { aem3000p01v1Entry 29 }

		-- 1.3.6.1.4.1.10106.3.101291.1.1.31
		aem3000p01v1Aes1BInput OBJECT-TYPE
			SYNTAX AnaMxInput1
			MAX-ACCESS read-write
			STATUS current
			DESCRIPTION
				"Allows selecting the embedded SDI audio channel that is routed to AES1 channel B"
		::= { aem3000p01v1Entry 31 }

		-- 1.3.6.1.4.1.10106.3.101291.1.1.33
		aem3000p01v1Aes2AInput OBJECT-TYPE
			SYNTAX AnaMxInput1
			MAX-ACCESS read-write
			STATUS current
			DESCRIPTION
				"Allows selecting the embedded SDI audio channel that is routed to AES2 channel A"
		::= { aem3000p01v1Entry 33 }

		-- 1.3.6.1.4.1.10106.3.101291.1.1.35
		aem3000p01v1Aes2BInput OBJECT-TYPE
			SYNTAX AnaMxInput1
			MAX-ACCESS read-write
			STATUS current
			DESCRIPTION
				"Allows selecting the embedded SDI audio channel that is routed to AES2 channel B"
		::= { aem3000p01v1Entry 35 }

		-- 1.3.6.1.4.1.10106.3.101291.1.1.37
		aem3000p01v1OverloadLevel OBJECT-TYPE
			SYNTAX LevelDbfs2
			MAX-ACCESS read-write
			STATUS current
			DESCRIPTION
				"Allows adjusting the threshold level for the overload detector"
		::= { aem3000p01v1Entry 37 }

		-- 1.3.6.1.4.1.10106.3.101291.1.1.39
		aem3000p01v1SilenceLevel OBJECT-TYPE
			SYNTAX LevelDbfs2
			MAX-ACCESS read-write
			STATUS current
			DESCRIPTION
				"Allows adjusting the threshold level for the silence detector"
		::= { aem3000p01v1Entry 39 }

		-- 1.3.6.1.4.1.10106.3.101291.1.1.41
		aem3000p01v1SilenceTime OBJECT-TYPE
			SYNTAX TimeS3
			MAX-ACCESS read-write
			STATUS current
			DESCRIPTION
				"Allows adjusting the time for the silence detector"
		::= { aem3000p01v1Entry 41 }

		-- 1.3.6.1.4.1.10106.3.101291.1.1.43
		aem3000p01v1NoSignal OBJECT-TYPE
			SYNTAX BitFail
			MAX-ACCESS read-only
			STATUS current
			DESCRIPTION
				"SDI input signal status"
		::= { aem3000p01v1Entry 43 }

		-- 1.3.6.1.4.1.10106.3.101291.1.1.44
		aem3000p01v1NoSignalTrapEnable OBJECT-TYPE
			SYNTAX AlarmEnable
			MAX-ACCESS read-write
			STATUS current
			DESCRIPTION
				"SDI input signal status Trap Enable"
		::= { aem3000p01v1Entry 44 }

		-- 1.3.6.1.4.1.10106.3.101291.1.1.45
		aem3000p01v1SilOut1 OBJECT-TYPE
			SYNTAX BitFail
			MAX-ACCESS read-only
			STATUS current
			DESCRIPTION
				"IN1 is in silence"
		::= { aem3000p01v1Entry 45 }

		-- 1.3.6.1.4.1.10106.3.101291.1.1.46
		aem3000p01v1SilOut1TrapEnable OBJECT-TYPE
			SYNTAX AlarmEnable
			MAX-ACCESS read-write
			STATUS current
			DESCRIPTION
				"IN1 is in silence Trap Enable"
		::= { aem3000p01v1Entry 46 }

		-- 1.3.6.1.4.1.10106.3.101291.1.1.47
		aem3000p01v1SilOut2 OBJECT-TYPE
			SYNTAX BitFail
			MAX-ACCESS read-only
			STATUS current
			DESCRIPTION
				"IN2 is in silence"
		::= { aem3000p01v1Entry 47 }

		-- 1.3.6.1.4.1.10106.3.101291.1.1.48
		aem3000p01v1SilOut2TrapEnable OBJECT-TYPE
			SYNTAX AlarmEnable
			MAX-ACCESS read-write
			STATUS current
			DESCRIPTION
				"IN2 is in silence Trap Enable"
		::= { aem3000p01v1Entry 48 }

		-- 1.3.6.1.4.1.10106.3.101291.1.1.49
		aem3000p01v1OvlOut1 OBJECT-TYPE
			SYNTAX BitFail
			MAX-ACCESS read-only
			STATUS current
			DESCRIPTION
				"IN1 is overloaded"
		::= { aem3000p01v1Entry 49 }

		-- 1.3.6.1.4.1.10106.3.101291.1.1.50
		aem3000p01v1OvlOut1TrapEnable OBJECT-TYPE
			SYNTAX AlarmEnable
			MAX-ACCESS read-write
			STATUS current
			DESCRIPTION
				"IN1 is overloaded Trap Enable"
		::= { aem3000p01v1Entry 50 }

		-- 1.3.6.1.4.1.10106.3.101291.1.1.51
		aem3000p01v1OvlOut2 OBJECT-TYPE
			SYNTAX BitFail
			MAX-ACCESS read-only
			STATUS current
			DESCRIPTION
				"IN2 is overloaded"
		::= { aem3000p01v1Entry 51 }

		-- 1.3.6.1.4.1.10106.3.101291.1.1.52
		aem3000p01v1OvlOut2TrapEnable OBJECT-TYPE
			SYNTAX AlarmEnable
			MAX-ACCESS read-write
			STATUS current
			DESCRIPTION
				"IN2 is overloaded Trap Enable"
		::= { aem3000p01v1Entry 52 }

		-- 1.3.6.1.4.1.10106.3.101291.1.1.53
		aem3000p01v1PckAGr1 OBJECT-TYPE
			SYNTAX Bit0No1Yes
			MAX-ACCESS read-only
			STATUS current
			DESCRIPTION
				"Group 1 normal audio packets (20 bits) detected"
		::= { aem3000p01v1Entry 53 }

		-- 1.3.6.1.4.1.10106.3.101291.1.1.55
		aem3000p01v1PckAGr2 OBJECT-TYPE
			SYNTAX Bit0No1Yes
			MAX-ACCESS read-only
			STATUS current
			DESCRIPTION
				"Group 2 normal audio packets (20 bits) detected"
		::= { aem3000p01v1Entry 55 }

		-- 1.3.6.1.4.1.10106.3.101291.1.1.57
		aem3000p01v1PckAGr3 OBJECT-TYPE
			SYNTAX Bit0No1Yes
			MAX-ACCESS read-only
			STATUS current
			DESCRIPTION
				"Group 3 normal audio packets (20 bits) detected"
		::= { aem3000p01v1Entry 57 }

		-- 1.3.6.1.4.1.10106.3.101291.1.1.59
		aem3000p01v1PckAGr4 OBJECT-TYPE
			SYNTAX Bit0No1Yes
			MAX-ACCESS read-only
			STATUS current
			DESCRIPTION
				"Group 4 normal audio packets (20 bits) detected"
		::= { aem3000p01v1Entry 59 }

		-- 1.3.6.1.4.1.10106.3.135801
		ade3000p01v1 OBJECT IDENTIFIER ::= { albalaProducts 135801 }

		-- 1.3.6.1.4.1.10106.3.135801.1
		ade3000p01v1Table  OBJECT-TYPE
			SYNTAX SEQUENCE OF Ade3000p01v1Entry
			MAX-ACCESS not-accessible
			STATUS current
			DESCRIPTION
				"Module  ADE3000P01V1 Table"
			::= { ade3000p01v1 1 }

		-- 1.3.6.1.4.1.10106.3.135801.1.1
		ade3000p01v1Entry  OBJECT-TYPE
			SYNTAX Ade3000p01v1Entry
			MAX-ACCESS not-accessible
			STATUS current
			DESCRIPTION
				"Module ADE3000P01V1 Entry"
			INDEX { ade3000p01v1Index }
			::= { ade3000p01v1Table 1 }

			Ade3000p01v1Entry ::=
			SEQUENCE {
				ade3000p01v1Index
				ModuleIndex,
				ade3000p01v1Group
				EmbedGroup,
				ade3000p01v1GroupTrapEnable
				AlarmEnable,
				ade3000p01v1GainAes1A
				Gain24dbMute,
				ade3000p01v1PhaseAes1A
				Bit0Nor1Inv,
				ade3000p01v1GainAes1B
				Gain24dbMute,
				ade3000p01v1PhaseAes1B
				Bit0Nor1Inv,
				ade3000p01v1GainAes2A
				Gain24dbMute,
				ade3000p01v1PhaseAes2A
				Bit0Nor1Inv,
				ade3000p01v1GainAes2B
				Gain24dbMute,
				ade3000p01v1PhaseAes2B
				Bit0Nor1Inv,
				ade3000p01v1Aes1AInput
				AesMxInput1,
				ade3000p01v1Aes1BInput
				AesMxInput1,
				ade3000p01v1Aes2AInput
				AesMxInput1,
				ade3000p01v1Aes2BInput
				AesMxInput1,
				ade3000p01v1MonoOut1
				Bit0No1Yes,
				ade3000p01v1MonoOut2
				Bit0No1Yes,
				ade3000p01v1MuteOut1
				Bit0No1Yes,
				ade3000p01v1MuteOut2
				Bit0No1Yes,
				ade3000p01v1OverloadLevel
				LevelDbfs2,
				ade3000p01v1SilenceLevel
				LevelDbfs2,
				ade3000p01v1SilenceTime
				TimeS3,
				ade3000p01v1ClnGr1
				Bit0No1Yes,
				ade3000p01v1ClnGr2
				Bit0No1Yes,
				ade3000p01v1ClnGr3
				Bit0No1Yes,
				ade3000p01v1ClnGr4
				Bit0No1Yes,
				ade3000p01v1NoSignal
				BitFail,
				ade3000p01v1NoSignalTrapEnable
				AlarmEnable,
				ade3000p01v1NsamAes1
				BitFail,
				ade3000p01v1NsamAes1TrapEnable
				AlarmEnable,
				ade3000p01v1NsamAes2
				BitFail,
				ade3000p01v1NsamAes2TrapEnable
				AlarmEnable,
				ade3000p01v1SilOut1
				BitFail,
				ade3000p01v1SilOut1TrapEnable
				AlarmEnable,
				ade3000p01v1SilOut2
				BitFail,
				ade3000p01v1SilOut2TrapEnable
				AlarmEnable,
				ade3000p01v1OvlOut1
				BitFail,
				ade3000p01v1OvlOut1TrapEnable
				AlarmEnable,
				ade3000p01v1OvlOut2
				BitFail,
				ade3000p01v1OvlOut2TrapEnable
				AlarmEnable,
				ade3000p01v1PckAGr1
				Bit0No1Yes,
				ade3000p01v1PckAGr2
				Bit0No1Yes,
				ade3000p01v1PckAGr3
				Bit0No1Yes,
				ade3000p01v1PckAGr4
				Bit0No1Yes
			 }

		-- 1.3.6.1.4.1.10106.3.101291.1.1.1
		ade3000p01v1Index OBJECT-TYPE
			SYNTAX ModuleIndex
			MAX-ACCESS read-only
			STATUS current
			DESCRIPTION
				"Index of ADE3000P01V1 Table"
		::= { ade3000p01v1Entry 1 }

		-- 1.3.6.1.4.1.10106.3.101291.1.1.3
		ade3000p01v1Group OBJECT-TYPE
			SYNTAX EmbedGroup
			MAX-ACCESS read-write
			STATUS current
			DESCRIPTION
				"Allows selecting the group from which the audio is deembedded"
		::= { ade3000p01v1Entry 3 }

		-- 1.3.6.1.4.1.10106.3.101291.1.1.4
		ade3000p01v1GroupTrapEnable OBJECT-TYPE
			SYNTAX AlarmEnable
			MAX-ACCESS read-write
			STATUS current
			DESCRIPTION
				"Allows selecting the group from which the audio is deembedded Trap Enable"
		::= { ade3000p01v1Entry 4 }

		-- 1.3.6.1.4.1.10106.3.101291.1.1.5
		ade3000p01v1GainAes1A OBJECT-TYPE
			SYNTAX Gain24dbMute
			MAX-ACCESS read-write
			STATUS current
			DESCRIPTION
				"Allows adjusting the gain of OUT1 channel A"
		::= { ade3000p01v1Entry 5 }

		-- 1.3.6.1.4.1.10106.3.101291.1.1.7
		ade3000p01v1PhaseAes1A OBJECT-TYPE
			SYNTAX Bit0Nor1Inv
			MAX-ACCESS read-write
			STATUS current
			DESCRIPTION
				"Allows changing the phase of OUT1 channel A"
		::= { ade3000p01v1Entry 7 }

		-- 1.3.6.1.4.1.10106.3.101291.1.1.9
		ade3000p01v1GainAes1B OBJECT-TYPE
			SYNTAX Gain24dbMute
			MAX-ACCESS read-write
			STATUS current
			DESCRIPTION
				"Allows adjusting the gain of OUT1 channel B"
		::= { ade3000p01v1Entry 9 }

		-- 1.3.6.1.4.1.10106.3.101291.1.1.11
		ade3000p01v1PhaseAes1B OBJECT-TYPE
			SYNTAX Bit0Nor1Inv
			MAX-ACCESS read-write
			STATUS current
			DESCRIPTION
				"Allows changing the phase of OUT1 channel B"
		::= { ade3000p01v1Entry 11 }

		-- 1.3.6.1.4.1.10106.3.101291.1.1.13
		ade3000p01v1GainAes2A OBJECT-TYPE
			SYNTAX Gain24dbMute
			MAX-ACCESS read-write
			STATUS current
			DESCRIPTION
				"Allows adjusting the gain of OUT2 channel A"
		::= { ade3000p01v1Entry 13 }

		-- 1.3.6.1.4.1.10106.3.101291.1.1.15
		ade3000p01v1PhaseAes2A OBJECT-TYPE
			SYNTAX Bit0Nor1Inv
			MAX-ACCESS read-write
			STATUS current
			DESCRIPTION
				"Allows changing the phase of OUT2 channel A"
		::= { ade3000p01v1Entry 15 }

		-- 1.3.6.1.4.1.10106.3.101291.1.1.17
		ade3000p01v1GainAes2B OBJECT-TYPE
			SYNTAX Gain24dbMute
			MAX-ACCESS read-write
			STATUS current
			DESCRIPTION
				"Allows adjusting the gain of OUT2 channel B"
		::= { ade3000p01v1Entry 17 }

		-- 1.3.6.1.4.1.10106.3.101291.1.1.19
		ade3000p01v1PhaseAes2B OBJECT-TYPE
			SYNTAX Bit0Nor1Inv
			MAX-ACCESS read-write
			STATUS current
			DESCRIPTION
				"Allows changing the phase of OUT2 channel B"
		::= { ade3000p01v1Entry 19 }

		-- 1.3.6.1.4.1.10106.3.101291.1.1.21
		ade3000p01v1Aes1AInput OBJECT-TYPE
			SYNTAX AesMxInput1
			MAX-ACCESS read-write
			STATUS current
			DESCRIPTION
				"Allows selecting the embedded SDI audio channel that is routed to OUT1 channel A"
		::= { ade3000p01v1Entry 21 }

		-- 1.3.6.1.4.1.10106.3.101291.1.1.23
		ade3000p01v1Aes1BInput OBJECT-TYPE
			SYNTAX AesMxInput1
			MAX-ACCESS read-write
			STATUS current
			DESCRIPTION
				"Allows selecting the embedded SDI audio channel that is routed to OUT1 channel B"
		::= { ade3000p01v1Entry 23 }

		-- 1.3.6.1.4.1.10106.3.101291.1.1.25
		ade3000p01v1Aes2AInput OBJECT-TYPE
			SYNTAX AesMxInput1
			MAX-ACCESS read-write
			STATUS current
			DESCRIPTION
				"Allows selecting the embedded SDI audio channel that is routed to OUT2 channel A"
		::= { ade3000p01v1Entry 25 }

		-- 1.3.6.1.4.1.10106.3.101291.1.1.27
		ade3000p01v1Aes2BInput OBJECT-TYPE
			SYNTAX AesMxInput1
			MAX-ACCESS read-write
			STATUS current
			DESCRIPTION
				"Allows selecting the embedded SDI audio channel that is routed to OUT2 channel B"
		::= { ade3000p01v1Entry 27 }

		-- 1.3.6.1.4.1.10106.3.101291.1.1.29
		ade3000p01v1MonoOut1 OBJECT-TYPE
			SYNTAX Bit0No1Yes
			MAX-ACCESS read-write
			STATUS current
			DESCRIPTION
				"Allows combining A&B channels to make a monophonic channel"
		::= { ade3000p01v1Entry 29 }

		-- 1.3.6.1.4.1.10106.3.101291.1.1.31
		ade3000p01v1MonoOut2 OBJECT-TYPE
			SYNTAX Bit0No1Yes
			MAX-ACCESS read-write
			STATUS current
			DESCRIPTION
				"Allows combining A&B channels to make a monophonic channel"
		::= { ade3000p01v1Entry 31 }

		-- 1.3.6.1.4.1.10106.3.101291.1.1.33
		ade3000p01v1MuteOut1 OBJECT-TYPE
			SYNTAX Bit0No1Yes
			MAX-ACCESS read-write
			STATUS current
			DESCRIPTION
				"Allows muting of both OUT1 channels"
		::= { ade3000p01v1Entry 33 }

		-- 1.3.6.1.4.1.10106.3.101291.1.1.35
		ade3000p01v1MuteOut2 OBJECT-TYPE
			SYNTAX Bit0No1Yes
			MAX-ACCESS read-write
			STATUS current
			DESCRIPTION
				"Allows muting of both OUT2 channels"
		::= { ade3000p01v1Entry 35 }

		-- 1.3.6.1.4.1.10106.3.101291.1.1.37
		ade3000p01v1OverloadLevel OBJECT-TYPE
			SYNTAX LevelDbfs2
			MAX-ACCESS read-write
			STATUS current
			DESCRIPTION
				"Allows adjusting the threshold level for the overload detector"
		::= { ade3000p01v1Entry 37 }

		-- 1.3.6.1.4.1.10106.3.101291.1.1.39
		ade3000p01v1SilenceLevel OBJECT-TYPE
			SYNTAX LevelDbfs2
			MAX-ACCESS read-write
			STATUS current
			DESCRIPTION
				"Allows adjusting the threshold level for the silence detector"
		::= { ade3000p01v1Entry 39 }

		-- 1.3.6.1.4.1.10106.3.101291.1.1.41
		ade3000p01v1SilenceTime OBJECT-TYPE
			SYNTAX TimeS3
			MAX-ACCESS read-write
			STATUS current
			DESCRIPTION
				"Allows adjusting the time for the silence detector"
		::= { ade3000p01v1Entry 41 }

		-- 1.3.6.1.4.1.10106.3.101291.1.1.43
		ade3000p01v1ClnGr1 OBJECT-TYPE
			SYNTAX Bit0No1Yes
			MAX-ACCESS read-write
			STATUS current
			DESCRIPTION
				"Allows selecting if all the group 1 audio packets are deleted after deembedding"
		::= { ade3000p01v1Entry 43 }

		-- 1.3.6.1.4.1.10106.3.101291.1.1.45
		ade3000p01v1ClnGr2 OBJECT-TYPE
			SYNTAX Bit0No1Yes
			MAX-ACCESS read-write
			STATUS current
			DESCRIPTION
				"Allows selecting if all the group 2 audio packets are deleted after deembedding"
		::= { ade3000p01v1Entry 45 }

		-- 1.3.6.1.4.1.10106.3.101291.1.1.47
		ade3000p01v1ClnGr3 OBJECT-TYPE
			SYNTAX Bit0No1Yes
			MAX-ACCESS read-write
			STATUS current
			DESCRIPTION
				"Allows selecting if all the group 3 audio packets are deleted after deembedding"
		::= { ade3000p01v1Entry 47 }

		-- 1.3.6.1.4.1.10106.3.101291.1.1.49
		ade3000p01v1ClnGr4 OBJECT-TYPE
			SYNTAX Bit0No1Yes
			MAX-ACCESS read-write
			STATUS current
			DESCRIPTION
				"Allows selecting if all the group 4 audio packets are deleted after deembedding"
		::= { ade3000p01v1Entry 49 }

		-- 1.3.6.1.4.1.10106.3.101291.1.1.51
		ade3000p01v1NoSignal OBJECT-TYPE
			SYNTAX BitFail
			MAX-ACCESS read-only
			STATUS current
			DESCRIPTION
				"SDI input signal status"
		::= { ade3000p01v1Entry 51 }

		-- 1.3.6.1.4.1.10106.3.101291.1.1.52
		ade3000p01v1NoSignalTrapEnable OBJECT-TYPE
			SYNTAX AlarmEnable
			MAX-ACCESS read-write
			STATUS current
			DESCRIPTION
				"SDI input signal status Trap Enable"
		::= { ade3000p01v1Entry 52 }

		-- 1.3.6.1.4.1.10106.3.101291.1.1.53
		ade3000p01v1NsamAes1 OBJECT-TYPE
			SYNTAX BitFail
			MAX-ACCESS read-only
			STATUS current
			DESCRIPTION
				"Bad number of samples per frame in AES1 signal"
		::= { ade3000p01v1Entry 53 }

		-- 1.3.6.1.4.1.10106.3.101291.1.1.54
		ade3000p01v1NsamAes1TrapEnable OBJECT-TYPE
			SYNTAX AlarmEnable
			MAX-ACCESS read-write
			STATUS current
			DESCRIPTION
				"Bad number of samples per frame in AES1 signal Trap Enable"
		::= { ade3000p01v1Entry 54 }

		-- 1.3.6.1.4.1.10106.3.101291.1.1.55
		ade3000p01v1NsamAes2 OBJECT-TYPE
			SYNTAX BitFail
			MAX-ACCESS read-only
			STATUS current
			DESCRIPTION
				"Bad number of samples per frame in AES2 signal"
		::= { ade3000p01v1Entry 55 }

		-- 1.3.6.1.4.1.10106.3.101291.1.1.56
		ade3000p01v1NsamAes2TrapEnable OBJECT-TYPE
			SYNTAX AlarmEnable
			MAX-ACCESS read-write
			STATUS current
			DESCRIPTION
				"Bad number of samples per frame in AES2 signal Trap Enable"
		::= { ade3000p01v1Entry 56 }

		-- 1.3.6.1.4.1.10106.3.101291.1.1.57
		ade3000p01v1SilOut1 OBJECT-TYPE
			SYNTAX BitFail
			MAX-ACCESS read-only
			STATUS current
			DESCRIPTION
				"OUT1 is in silence"
		::= { ade3000p01v1Entry 57 }

		-- 1.3.6.1.4.1.10106.3.101291.1.1.58
		ade3000p01v1SilOut1TrapEnable OBJECT-TYPE
			SYNTAX AlarmEnable
			MAX-ACCESS read-write
			STATUS current
			DESCRIPTION
				"OUT1 is in silence Trap Enable"
		::= { ade3000p01v1Entry 58 }

		-- 1.3.6.1.4.1.10106.3.101291.1.1.59
		ade3000p01v1SilOut2 OBJECT-TYPE
			SYNTAX BitFail
			MAX-ACCESS read-only
			STATUS current
			DESCRIPTION
				"OUT2 is in silence"
		::= { ade3000p01v1Entry 59 }

		-- 1.3.6.1.4.1.10106.3.101291.1.1.60
		ade3000p01v1SilOut2TrapEnable OBJECT-TYPE
			SYNTAX AlarmEnable
			MAX-ACCESS read-write
			STATUS current
			DESCRIPTION
				"OUT2 is in silence Trap Enable"
		::= { ade3000p01v1Entry 60 }

		-- 1.3.6.1.4.1.10106.3.101291.1.1.61
		ade3000p01v1OvlOut1 OBJECT-TYPE
			SYNTAX BitFail
			MAX-ACCESS read-only
			STATUS current
			DESCRIPTION
				"OUT1 is overloaded"
		::= { ade3000p01v1Entry 61 }

		-- 1.3.6.1.4.1.10106.3.101291.1.1.62
		ade3000p01v1OvlOut1TrapEnable OBJECT-TYPE
			SYNTAX AlarmEnable
			MAX-ACCESS read-write
			STATUS current
			DESCRIPTION
				"OUT1 is overloaded Trap Enable"
		::= { ade3000p01v1Entry 62 }

		-- 1.3.6.1.4.1.10106.3.101291.1.1.63
		ade3000p01v1OvlOut2 OBJECT-TYPE
			SYNTAX BitFail
			MAX-ACCESS read-only
			STATUS current
			DESCRIPTION
				"OUT2 is overloaded"
		::= { ade3000p01v1Entry 63 }

		-- 1.3.6.1.4.1.10106.3.101291.1.1.64
		ade3000p01v1OvlOut2TrapEnable OBJECT-TYPE
			SYNTAX AlarmEnable
			MAX-ACCESS read-write
			STATUS current
			DESCRIPTION
				"OUT2 is overloaded Trap Enable"
		::= { ade3000p01v1Entry 64 }

		-- 1.3.6.1.4.1.10106.3.101291.1.1.65
		ade3000p01v1PckAGr1 OBJECT-TYPE
			SYNTAX Bit0No1Yes
			MAX-ACCESS read-only
			STATUS current
			DESCRIPTION
				"Group 1 normal audio packets (20 bits) detected"
		::= { ade3000p01v1Entry 65 }

		-- 1.3.6.1.4.1.10106.3.101291.1.1.67
		ade3000p01v1PckAGr2 OBJECT-TYPE
			SYNTAX Bit0No1Yes
			MAX-ACCESS read-only
			STATUS current
			DESCRIPTION
				"Group 2 normal audio packets (20 bits) detected"
		::= { ade3000p01v1Entry 67 }

		-- 1.3.6.1.4.1.10106.3.101291.1.1.69
		ade3000p01v1PckAGr3 OBJECT-TYPE
			SYNTAX Bit0No1Yes
			MAX-ACCESS read-only
			STATUS current
			DESCRIPTION
				"Group 3 normal audio packets (20 bits) detected"
		::= { ade3000p01v1Entry 69 }

		-- 1.3.6.1.4.1.10106.3.101291.1.1.71
		ade3000p01v1PckAGr4 OBJECT-TYPE
			SYNTAX Bit0No1Yes
			MAX-ACCESS read-only
			STATUS current
			DESCRIPTION
				"Group 4 normal audio packets (20 bits) detected"
		::= { ade3000p01v1Entry 71 }

		-- 1.3.6.1.4.1.10106.3.136301
		dsw3000c02v1 OBJECT IDENTIFIER ::= { albalaProducts 136301 }

		-- 1.3.6.1.4.1.10106.3.136301.1
		dsw3000c02v1Table  OBJECT-TYPE
			SYNTAX SEQUENCE OF Dsw3000c02v1Entry
			MAX-ACCESS not-accessible
			STATUS current
			DESCRIPTION
				"Module  DSW3000C02V1 Table"
			::= { dsw3000c02v1 1 }

		-- 1.3.6.1.4.1.10106.3.136301.1.1
		dsw3000c02v1Entry  OBJECT-TYPE
			SYNTAX Dsw3000c02v1Entry
			MAX-ACCESS not-accessible
			STATUS current
			DESCRIPTION
				"Module DSW3000C02V1 Entry"
			INDEX { dsw3000c02v1Index }
			::= { dsw3000c02v1Table 1 }

			Dsw3000c02v1Entry ::=
			SEQUENCE {
				dsw3000c02v1Index
				ModuleIndex,
				dsw3000c02v1Mode
				ChgOverMode2,
				dsw3000c02v1ModeTrapEnable
				AlarmEnable,
				dsw3000c02v1Buzzer
				BitMask,
				dsw3000c02v1Input
				ChgOverInput1,
				dsw3000c02v1InputTrapEnable
				AlarmEnable,
				dsw3000c02v1MainFail
				BitFail,
				dsw3000c02v1MainFailTrapEnable
				AlarmEnable,
				dsw3000c02v1ExtMainFail
				BitFail,
				dsw3000c02v1ExtMainFailTrapEnable
				AlarmEnable,
				dsw3000c02v1ResFail
				BitFail,
				dsw3000c02v1ResFailTrapEnable
				AlarmEnable,
				dsw3000c02v1ExtResFail
				BitFail,
				dsw3000c02v1ExtResFailTrapEnable
				AlarmEnable,
				dsw3000c02v1AuxFail
				BitFail,
				dsw3000c02v1AuxFailTrapEnable
				AlarmEnable,
				dsw3000c02v1ExtAuxFail
				BitFail,
				dsw3000c02v1ExtAuxFailTrapEnable
				AlarmEnable
			 }

		-- 1.3.6.1.4.1.10106.3.101291.1.1.1
		dsw3000c02v1Index OBJECT-TYPE
			SYNTAX ModuleIndex
			MAX-ACCESS read-only
			STATUS current
			DESCRIPTION
				"Index of DSW3000C02V1 Table"
		::= { dsw3000c02v1Entry 1 }

		-- 1.3.6.1.4.1.10106.3.101291.1.1.3
		dsw3000c02v1Mode OBJECT-TYPE
			SYNTAX ChgOverMode2
			MAX-ACCESS read-write
			STATUS current
			DESCRIPTION
				"Allows selecting the switching mode"
		::= { dsw3000c02v1Entry 3 }

		-- 1.3.6.1.4.1.10106.3.101291.1.1.4
		dsw3000c02v1ModeTrapEnable OBJECT-TYPE
			SYNTAX AlarmEnable
			MAX-ACCESS read-write
			STATUS current
			DESCRIPTION
				"Allows selecting the switching mode Trap Enable"
		::= { dsw3000c02v1Entry 4 }

		-- 1.3.6.1.4.1.10106.3.101291.1.1.5
		dsw3000c02v1Buzzer OBJECT-TYPE
			SYNTAX BitMask
			MAX-ACCESS read-write
			STATUS current
			DESCRIPTION
				"Allows buzzer operation"
		::= { dsw3000c02v1Entry 5 }

		-- 1.3.6.1.4.1.10106.3.101291.1.1.7
		dsw3000c02v1Input OBJECT-TYPE
			SYNTAX ChgOverInput1
			MAX-ACCESS read-write
			STATUS current
			DESCRIPTION
				"Selected input"
		::= { dsw3000c02v1Entry 7 }

		-- 1.3.6.1.4.1.10106.3.101291.1.1.8
		dsw3000c02v1InputTrapEnable OBJECT-TYPE
			SYNTAX AlarmEnable
			MAX-ACCESS read-write
			STATUS current
			DESCRIPTION
				"Selected input Trap Enable"
		::= { dsw3000c02v1Entry 8 }

		-- 1.3.6.1.4.1.10106.3.101291.1.1.9
		dsw3000c02v1MainFail OBJECT-TYPE
			SYNTAX BitFail
			MAX-ACCESS read-only
			STATUS current
			DESCRIPTION
				"Main input status"
		::= { dsw3000c02v1Entry 9 }

		-- 1.3.6.1.4.1.10106.3.101291.1.1.10
		dsw3000c02v1MainFailTrapEnable OBJECT-TYPE
			SYNTAX AlarmEnable
			MAX-ACCESS read-write
			STATUS current
			DESCRIPTION
				"Main input status Trap Enable"
		::= { dsw3000c02v1Entry 10 }

		-- 1.3.6.1.4.1.10106.3.101291.1.1.11
		dsw3000c02v1ExtMainFail OBJECT-TYPE
			SYNTAX BitFail
			MAX-ACCESS read-only
			STATUS current
			DESCRIPTION
				"Main external input fail status"
		::= { dsw3000c02v1Entry 11 }

		-- 1.3.6.1.4.1.10106.3.101291.1.1.12
		dsw3000c02v1ExtMainFailTrapEnable OBJECT-TYPE
			SYNTAX AlarmEnable
			MAX-ACCESS read-write
			STATUS current
			DESCRIPTION
				"Main external input fail status Trap Enable"
		::= { dsw3000c02v1Entry 12 }

		-- 1.3.6.1.4.1.10106.3.101291.1.1.13
		dsw3000c02v1ResFail OBJECT-TYPE
			SYNTAX BitFail
			MAX-ACCESS read-only
			STATUS current
			DESCRIPTION
				"Reserve input status"
		::= { dsw3000c02v1Entry 13 }

		-- 1.3.6.1.4.1.10106.3.101291.1.1.14
		dsw3000c02v1ResFailTrapEnable OBJECT-TYPE
			SYNTAX AlarmEnable
			MAX-ACCESS read-write
			STATUS current
			DESCRIPTION
				"Reserve input status Trap Enable"
		::= { dsw3000c02v1Entry 14 }

		-- 1.3.6.1.4.1.10106.3.101291.1.1.15
		dsw3000c02v1ExtResFail OBJECT-TYPE
			SYNTAX BitFail
			MAX-ACCESS read-only
			STATUS current
			DESCRIPTION
				"Reserve external input fail status"
		::= { dsw3000c02v1Entry 15 }

		-- 1.3.6.1.4.1.10106.3.101291.1.1.16
		dsw3000c02v1ExtResFailTrapEnable OBJECT-TYPE
			SYNTAX AlarmEnable
			MAX-ACCESS read-write
			STATUS current
			DESCRIPTION
				"Reserve external input fail status Trap Enable"
		::= { dsw3000c02v1Entry 16 }

		-- 1.3.6.1.4.1.10106.3.101291.1.1.17
		dsw3000c02v1AuxFail OBJECT-TYPE
			SYNTAX BitFail
			MAX-ACCESS read-only
			STATUS current
			DESCRIPTION
				"Auxiliar input status"
		::= { dsw3000c02v1Entry 17 }

		-- 1.3.6.1.4.1.10106.3.101291.1.1.18
		dsw3000c02v1AuxFailTrapEnable OBJECT-TYPE
			SYNTAX AlarmEnable
			MAX-ACCESS read-write
			STATUS current
			DESCRIPTION
				"Auxiliar input status Trap Enable"
		::= { dsw3000c02v1Entry 18 }

		-- 1.3.6.1.4.1.10106.3.101291.1.1.19
		dsw3000c02v1ExtAuxFail OBJECT-TYPE
			SYNTAX BitFail
			MAX-ACCESS read-only
			STATUS current
			DESCRIPTION
				"Auxiliar external input fail status"
		::= { dsw3000c02v1Entry 19 }

		-- 1.3.6.1.4.1.10106.3.101291.1.1.20
		dsw3000c02v1ExtAuxFailTrapEnable OBJECT-TYPE
			SYNTAX AlarmEnable
			MAX-ACCESS read-write
			STATUS current
			DESCRIPTION
				"Auxiliar external input fail status Trap Enable"
		::= { dsw3000c02v1Entry 20 }

		-- 1.3.6.1.4.1.10106.3.136601
		dem3000p01v1 OBJECT IDENTIFIER ::= { albalaProducts 136601 }

		-- 1.3.6.1.4.1.10106.3.136601.1
		dem3000p01v1Table  OBJECT-TYPE
			SYNTAX SEQUENCE OF Dem3000p01v1Entry
			MAX-ACCESS not-accessible
			STATUS current
			DESCRIPTION
				"Module  DEM3000P01V1 Table"
			::= { dem3000p01v1 1 }

		-- 1.3.6.1.4.1.10106.3.136601.1.1
		dem3000p01v1Entry  OBJECT-TYPE
			SYNTAX Dem3000p01v1Entry
			MAX-ACCESS not-accessible
			STATUS current
			DESCRIPTION
				"Module DEM3000P01V1 Entry"
			INDEX { dem3000p01v1Index }
			::= { dem3000p01v1Table 1 }

			Dem3000p01v1Entry ::=
			SEQUENCE {
				dem3000p01v1Index
				ModuleIndex,
				dem3000p01v1EmbedInsA
				Bit0No1Yes,
				dem3000p01v1EmbedModeA
				Bit0Clr1App,
				dem3000p01v1EmbedChA
				Bit0214,
				dem3000p01v1EmbedInsB
				Bit0No1Yes,
				dem3000p01v1EmbedModeB
				Bit0Clr1App,
				dem3000p01v1EmbedChB
				Bit0214,
				dem3000p01v1EmbedBits
				Bit024120,
				dem3000p01v1OperatingMode
				BitEmbed1,
				dem3000p01v1GroupA
				EmbedGroup,
				dem3000p01v1GroupATrapEnable
				AlarmEnable,
				dem3000p01v1GroupB
				EmbedGroup,
				dem3000p01v1GroupBTrapEnable
				AlarmEnable,
				dem3000p01v1NoSignalA
				BitFail,
				dem3000p01v1NoSignalATrapEnable
				AlarmEnable,
				dem3000p01v1NoAes1A
				BitFail,
				dem3000p01v1NoAes1ATrapEnable
				AlarmEnable,
				dem3000p01v1UlckAes1A
				BitFail,
				dem3000p01v1UlckAes1ATrapEnable
				AlarmEnable,
				dem3000p01v1NoAes2A
				BitFail,
				dem3000p01v1NoAes2ATrapEnable
				AlarmEnable,
				dem3000p01v1UlckAes2A
				BitFail,
				dem3000p01v1UlckAes2ATrapEnable
				AlarmEnable,
				dem3000p01v1PckAGr1A
				Bit0No1Yes,
				dem3000p01v1PckAGr2A
				Bit0No1Yes,
				dem3000p01v1PckAGr3A
				Bit0No1Yes,
				dem3000p01v1PckAGr4A
				Bit0No1Yes,
				dem3000p01v1NoSignalB
				BitFail,
				dem3000p01v1NoSignalBTrapEnable
				AlarmEnable,
				dem3000p01v1NoAes1B
				BitFail,
				dem3000p01v1NoAes1BTrapEnable
				AlarmEnable,
				dem3000p01v1UlckAes1B
				BitFail,
				dem3000p01v1UlckAes1BTrapEnable
				AlarmEnable,
				dem3000p01v1NoAes2B
				BitFail,
				dem3000p01v1NoAes2BTrapEnable
				AlarmEnable,
				dem3000p01v1UlckAes2B
				BitFail,
				dem3000p01v1UlckAes2BTrapEnable
				AlarmEnable,
				dem3000p01v1PckAGr1B
				Bit0No1Yes,
				dem3000p01v1PckAGr2B
				Bit0No1Yes,
				dem3000p01v1PckAGr3B
				Bit0No1Yes,
				dem3000p01v1PckAGr4B
				Bit0No1Yes
			 }

		-- 1.3.6.1.4.1.10106.3.101291.1.1.1
		dem3000p01v1Index OBJECT-TYPE
			SYNTAX ModuleIndex
			MAX-ACCESS read-only
			STATUS current
			DESCRIPTION
				"Index of DEM3000P01V1 Table"
		::= { dem3000p01v1Entry 1 }

		-- 1.3.6.1.4.1.10106.3.101291.1.1.3
		dem3000p01v1EmbedInsA OBJECT-TYPE
			SYNTAX Bit0No1Yes
			MAX-ACCESS read-write
			STATUS current
			DESCRIPTION
				"Allows selecting if the audio is embedded"
		::= { dem3000p01v1Entry 3 }

		-- 1.3.6.1.4.1.10106.3.101291.1.1.5
		dem3000p01v1EmbedModeA OBJECT-TYPE
			SYNTAX Bit0Clr1App
			MAX-ACCESS read-write
			STATUS current
			DESCRIPTION
				"Allows selecting if the incoming audio groups are deleted before embedding"
		::= { dem3000p01v1Entry 5 }

		-- 1.3.6.1.4.1.10106.3.101291.1.1.7
		dem3000p01v1EmbedChA OBJECT-TYPE
			SYNTAX Bit0214
			MAX-ACCESS read-write
			STATUS current
			DESCRIPTION
				"Allows selecting the number of AES frames embedded in the group"
		::= { dem3000p01v1Entry 7 }

		-- 1.3.6.1.4.1.10106.3.101291.1.1.9
		dem3000p01v1EmbedInsB OBJECT-TYPE
			SYNTAX Bit0No1Yes
			MAX-ACCESS read-write
			STATUS current
			DESCRIPTION
				"Allows selecting if the audio is embedded"
		::= { dem3000p01v1Entry 9 }

		-- 1.3.6.1.4.1.10106.3.101291.1.1.11
		dem3000p01v1EmbedModeB OBJECT-TYPE
			SYNTAX Bit0Clr1App
			MAX-ACCESS read-write
			STATUS current
			DESCRIPTION
				"Allows selecting if the incoming audio groups are deleted before embedding"
		::= { dem3000p01v1Entry 11 }

		-- 1.3.6.1.4.1.10106.3.101291.1.1.13
		dem3000p01v1EmbedChB OBJECT-TYPE
			SYNTAX Bit0214
			MAX-ACCESS read-write
			STATUS current
			DESCRIPTION
				"Allows selecting the number of AES frames embedded in the group"
		::= { dem3000p01v1Entry 13 }

		-- 1.3.6.1.4.1.10106.3.101291.1.1.15
		dem3000p01v1EmbedBits OBJECT-TYPE
			SYNTAX Bit024120
			MAX-ACCESS read-write
			STATUS current
			DESCRIPTION
				"Allows selecting the number of bits of the embedded audio"
		::= { dem3000p01v1Entry 15 }

		-- 1.3.6.1.4.1.10106.3.101291.1.1.17
		dem3000p01v1OperatingMode OBJECT-TYPE
			SYNTAX BitEmbed1
			MAX-ACCESS read-write
			STATUS current
			DESCRIPTION
				"Allows selecting if the module acts as two one group embedders or as one two groups embedder"
		::= { dem3000p01v1Entry 17 }

		-- 1.3.6.1.4.1.10106.3.101291.1.1.19
		dem3000p01v1GroupA OBJECT-TYPE
			SYNTAX EmbedGroup
			MAX-ACCESS read-write
			STATUS current
			DESCRIPTION
				"Allows selecting the group in which the audio is embedded"
		::= { dem3000p01v1Entry 19 }

		-- 1.3.6.1.4.1.10106.3.101291.1.1.20
		dem3000p01v1GroupATrapEnable OBJECT-TYPE
			SYNTAX AlarmEnable
			MAX-ACCESS read-write
			STATUS current
			DESCRIPTION
				"Allows selecting the group in which the audio is embedded Trap Enable"
		::= { dem3000p01v1Entry 20 }

		-- 1.3.6.1.4.1.10106.3.101291.1.1.21
		dem3000p01v1GroupB OBJECT-TYPE
			SYNTAX EmbedGroup
			MAX-ACCESS read-write
			STATUS current
			DESCRIPTION
				"Allows selecting the group in which the audio is embedded"
		::= { dem3000p01v1Entry 21 }

		-- 1.3.6.1.4.1.10106.3.101291.1.1.22
		dem3000p01v1GroupBTrapEnable OBJECT-TYPE
			SYNTAX AlarmEnable
			MAX-ACCESS read-write
			STATUS current
			DESCRIPTION
				"Allows selecting the group in which the audio is embedded Trap Enable"
		::= { dem3000p01v1Entry 22 }

		-- 1.3.6.1.4.1.10106.3.101291.1.1.23
		dem3000p01v1NoSignalA OBJECT-TYPE
			SYNTAX BitFail
			MAX-ACCESS read-only
			STATUS current
			DESCRIPTION
				"SDI input signal status"
		::= { dem3000p01v1Entry 23 }

		-- 1.3.6.1.4.1.10106.3.101291.1.1.24
		dem3000p01v1NoSignalATrapEnable OBJECT-TYPE
			SYNTAX AlarmEnable
			MAX-ACCESS read-write
			STATUS current
			DESCRIPTION
				"SDI input signal status Trap Enable"
		::= { dem3000p01v1Entry 24 }

		-- 1.3.6.1.4.1.10106.3.101291.1.1.25
		dem3000p01v1NoAes1A OBJECT-TYPE
			SYNTAX BitFail
			MAX-ACCESS read-only
			STATUS current
			DESCRIPTION
				"AES1 input signal status"
		::= { dem3000p01v1Entry 25 }

		-- 1.3.6.1.4.1.10106.3.101291.1.1.26
		dem3000p01v1NoAes1ATrapEnable OBJECT-TYPE
			SYNTAX AlarmEnable
			MAX-ACCESS read-write
			STATUS current
			DESCRIPTION
				"AES1 input signal status Trap Enable"
		::= { dem3000p01v1Entry 26 }

		-- 1.3.6.1.4.1.10106.3.101291.1.1.27
		dem3000p01v1UlckAes1A OBJECT-TYPE
			SYNTAX BitFail
			MAX-ACCESS read-only
			STATUS current
			DESCRIPTION
				"Indicates AES1 signal unlock fail"
		::= { dem3000p01v1Entry 27 }

		-- 1.3.6.1.4.1.10106.3.101291.1.1.28
		dem3000p01v1UlckAes1ATrapEnable OBJECT-TYPE
			SYNTAX AlarmEnable
			MAX-ACCESS read-write
			STATUS current
			DESCRIPTION
				"Indicates AES1 signal unlock fail Trap Enable"
		::= { dem3000p01v1Entry 28 }

		-- 1.3.6.1.4.1.10106.3.101291.1.1.29
		dem3000p01v1NoAes2A OBJECT-TYPE
			SYNTAX BitFail
			MAX-ACCESS read-only
			STATUS current
			DESCRIPTION
				"AES2 input signal status"
		::= { dem3000p01v1Entry 29 }

		-- 1.3.6.1.4.1.10106.3.101291.1.1.30
		dem3000p01v1NoAes2ATrapEnable OBJECT-TYPE
			SYNTAX AlarmEnable
			MAX-ACCESS read-write
			STATUS current
			DESCRIPTION
				"AES2 input signal status Trap Enable"
		::= { dem3000p01v1Entry 30 }

		-- 1.3.6.1.4.1.10106.3.101291.1.1.31
		dem3000p01v1UlckAes2A OBJECT-TYPE
			SYNTAX BitFail
			MAX-ACCESS read-only
			STATUS current
			DESCRIPTION
				"Indicates AES2 signal unlock fail"
		::= { dem3000p01v1Entry 31 }

		-- 1.3.6.1.4.1.10106.3.101291.1.1.32
		dem3000p01v1UlckAes2ATrapEnable OBJECT-TYPE
			SYNTAX AlarmEnable
			MAX-ACCESS read-write
			STATUS current
			DESCRIPTION
				"Indicates AES2 signal unlock fail Trap Enable"
		::= { dem3000p01v1Entry 32 }

		-- 1.3.6.1.4.1.10106.3.101291.1.1.33
		dem3000p01v1PckAGr1A OBJECT-TYPE
			SYNTAX Bit0No1Yes
			MAX-ACCESS read-only
			STATUS current
			DESCRIPTION
				"Group 1 normal audio packets (20 bits) detected"
		::= { dem3000p01v1Entry 33 }

		-- 1.3.6.1.4.1.10106.3.101291.1.1.35
		dem3000p01v1PckAGr2A OBJECT-TYPE
			SYNTAX Bit0No1Yes
			MAX-ACCESS read-only
			STATUS current
			DESCRIPTION
				"Group 2 normal audio packets (20 bits) detected"
		::= { dem3000p01v1Entry 35 }

		-- 1.3.6.1.4.1.10106.3.101291.1.1.37
		dem3000p01v1PckAGr3A OBJECT-TYPE
			SYNTAX Bit0No1Yes
			MAX-ACCESS read-only
			STATUS current
			DESCRIPTION
				"Group 3 normal audio packets (20 bits) detected"
		::= { dem3000p01v1Entry 37 }

		-- 1.3.6.1.4.1.10106.3.101291.1.1.39
		dem3000p01v1PckAGr4A OBJECT-TYPE
			SYNTAX Bit0No1Yes
			MAX-ACCESS read-only
			STATUS current
			DESCRIPTION
				"Group 4 normal audio packets (20 bits) detected"
		::= { dem3000p01v1Entry 39 }

		-- 1.3.6.1.4.1.10106.3.101291.1.1.41
		dem3000p01v1NoSignalB OBJECT-TYPE
			SYNTAX BitFail
			MAX-ACCESS read-only
			STATUS current
			DESCRIPTION
				"SDI input signal status"
		::= { dem3000p01v1Entry 41 }

		-- 1.3.6.1.4.1.10106.3.101291.1.1.42
		dem3000p01v1NoSignalBTrapEnable OBJECT-TYPE
			SYNTAX AlarmEnable
			MAX-ACCESS read-write
			STATUS current
			DESCRIPTION
				"SDI input signal status Trap Enable"
		::= { dem3000p01v1Entry 42 }

		-- 1.3.6.1.4.1.10106.3.101291.1.1.43
		dem3000p01v1NoAes1B OBJECT-TYPE
			SYNTAX BitFail
			MAX-ACCESS read-only
			STATUS current
			DESCRIPTION
				"AES1 input signal status"
		::= { dem3000p01v1Entry 43 }

		-- 1.3.6.1.4.1.10106.3.101291.1.1.44
		dem3000p01v1NoAes1BTrapEnable OBJECT-TYPE
			SYNTAX AlarmEnable
			MAX-ACCESS read-write
			STATUS current
			DESCRIPTION
				"AES1 input signal status Trap Enable"
		::= { dem3000p01v1Entry 44 }

		-- 1.3.6.1.4.1.10106.3.101291.1.1.45
		dem3000p01v1UlckAes1B OBJECT-TYPE
			SYNTAX BitFail
			MAX-ACCESS read-only
			STATUS current
			DESCRIPTION
				"Indicates AES1 signal unlock fail"
		::= { dem3000p01v1Entry 45 }

		-- 1.3.6.1.4.1.10106.3.101291.1.1.46
		dem3000p01v1UlckAes1BTrapEnable OBJECT-TYPE
			SYNTAX AlarmEnable
			MAX-ACCESS read-write
			STATUS current
			DESCRIPTION
				"Indicates AES1 signal unlock fail Trap Enable"
		::= { dem3000p01v1Entry 46 }

		-- 1.3.6.1.4.1.10106.3.101291.1.1.47
		dem3000p01v1NoAes2B OBJECT-TYPE
			SYNTAX BitFail
			MAX-ACCESS read-only
			STATUS current
			DESCRIPTION
				"AES2 input signal status"
		::= { dem3000p01v1Entry 47 }

		-- 1.3.6.1.4.1.10106.3.101291.1.1.48
		dem3000p01v1NoAes2BTrapEnable OBJECT-TYPE
			SYNTAX AlarmEnable
			MAX-ACCESS read-write
			STATUS current
			DESCRIPTION
				"AES2 input signal status Trap Enable"
		::= { dem3000p01v1Entry 48 }

		-- 1.3.6.1.4.1.10106.3.101291.1.1.49
		dem3000p01v1UlckAes2B OBJECT-TYPE
			SYNTAX BitFail
			MAX-ACCESS read-only
			STATUS current
			DESCRIPTION
				"Indicates AES2 signal unlock fail"
		::= { dem3000p01v1Entry 49 }

		-- 1.3.6.1.4.1.10106.3.101291.1.1.50
		dem3000p01v1UlckAes2BTrapEnable OBJECT-TYPE
			SYNTAX AlarmEnable
			MAX-ACCESS read-write
			STATUS current
			DESCRIPTION
				"Indicates AES2 signal unlock fail Trap Enable"
		::= { dem3000p01v1Entry 50 }

		-- 1.3.6.1.4.1.10106.3.101291.1.1.51
		dem3000p01v1PckAGr1B OBJECT-TYPE
			SYNTAX Bit0No1Yes
			MAX-ACCESS read-only
			STATUS current
			DESCRIPTION
				"Group 1 normal audio packets (20 bits) detected"
		::= { dem3000p01v1Entry 51 }

		-- 1.3.6.1.4.1.10106.3.101291.1.1.53
		dem3000p01v1PckAGr2B OBJECT-TYPE
			SYNTAX Bit0No1Yes
			MAX-ACCESS read-only
			STATUS current
			DESCRIPTION
				"Group 2 normal audio packets (20 bits) detected"
		::= { dem3000p01v1Entry 53 }

		-- 1.3.6.1.4.1.10106.3.101291.1.1.55
		dem3000p01v1PckAGr3B OBJECT-TYPE
			SYNTAX Bit0No1Yes
			MAX-ACCESS read-only
			STATUS current
			DESCRIPTION
				"Group 3 normal audio packets (20 bits) detected"
		::= { dem3000p01v1Entry 55 }

		-- 1.3.6.1.4.1.10106.3.101291.1.1.57
		dem3000p01v1PckAGr4B OBJECT-TYPE
			SYNTAX Bit0No1Yes
			MAX-ACCESS read-only
			STATUS current
			DESCRIPTION
				"Group 4 normal audio packets (20 bits) detected"
		::= { dem3000p01v1Entry 57 }

		-- 1.3.6.1.4.1.10106.3.137101
		dde3000p01v1 OBJECT IDENTIFIER ::= { albalaProducts 137101 }

		-- 1.3.6.1.4.1.10106.3.137101.1
		dde3000p01v1Table  OBJECT-TYPE
			SYNTAX SEQUENCE OF Dde3000p01v1Entry
			MAX-ACCESS not-accessible
			STATUS current
			DESCRIPTION
				"Module  DDE3000P01V1 Table"
			::= { dde3000p01v1 1 }

		-- 1.3.6.1.4.1.10106.3.137101.1.1
		dde3000p01v1Entry  OBJECT-TYPE
			SYNTAX Dde3000p01v1Entry
			MAX-ACCESS not-accessible
			STATUS current
			DESCRIPTION
				"Module DDE3000P01V1 Entry"
			INDEX { dde3000p01v1Index }
			::= { dde3000p01v1Table 1 }

			Dde3000p01v1Entry ::=
			SEQUENCE {
				dde3000p01v1Index
				ModuleIndex,
				dde3000p01v1OperatingMode
				BitEmbed1,
				dde3000p01v1GroupA
				EmbedGroup,
				dde3000p01v1GroupATrapEnable
				AlarmEnable,
				dde3000p01v1GroupB
				EmbedGroup,
				dde3000p01v1GroupBTrapEnable
				AlarmEnable,
				dde3000p01v1ClnGr1A
				Bit0No1Yes,
				dde3000p01v1ClnGr2A
				Bit0No1Yes,
				dde3000p01v1ClnGr3A
				Bit0No1Yes,
				dde3000p01v1ClnGr4A
				Bit0No1Yes,
				dde3000p01v1ClnGr1B
				Bit0No1Yes,
				dde3000p01v1ClnGr2B
				Bit0No1Yes,
				dde3000p01v1ClnGr3B
				Bit0No1Yes,
				dde3000p01v1ClnGr4B
				Bit0No1Yes,
				dde3000p01v1MuteAes1A
				Bit0No1Yes,
				dde3000p01v1PhInvAes1A
				Bit0No1Yes,
				dde3000p01v1SwapAes1A
				Bit0No1Yes,
				dde3000p01v1MuteAes2A
				Bit0No1Yes,
				dde3000p01v1PhInvAes2A
				Bit0No1Yes,
				dde3000p01v1SwapAes2A
				Bit0No1Yes,
				dde3000p01v1SwapAesA
				Bit0No1Yes,
				dde3000p01v1MuteAes1B
				Bit0No1Yes,
				dde3000p01v1PhInvAes1B
				Bit0No1Yes,
				dde3000p01v1SwapAes1B
				Bit0No1Yes,
				dde3000p01v1MuteAes2B
				Bit0No1Yes,
				dde3000p01v1PhInvAes2B
				Bit0No1Yes,
				dde3000p01v1SwapAes2B
				Bit0No1Yes,
				dde3000p01v1SwapAesB
				Bit0No1Yes,
				dde3000p01v1NoSignalA
				BitFail,
				dde3000p01v1NoSignalATrapEnable
				AlarmEnable,
				dde3000p01v1NsamAes1A
				BitFail,
				dde3000p01v1NsamAes1ATrapEnable
				AlarmEnable,
				dde3000p01v1NsamAes2A
				BitFail,
				dde3000p01v1NsamAes2ATrapEnable
				AlarmEnable,
				dde3000p01v1PckAGr1A
				Bit0No1Yes,
				dde3000p01v1PckAGr2A
				Bit0No1Yes,
				dde3000p01v1PckAGr3A
				Bit0No1Yes,
				dde3000p01v1PckAGr4A
				Bit0No1Yes,
				dde3000p01v1NoSignalB
				BitFail,
				dde3000p01v1NoSignalBTrapEnable
				AlarmEnable,
				dde3000p01v1NsamAes1B
				BitFail,
				dde3000p01v1NsamAes1BTrapEnable
				AlarmEnable,
				dde3000p01v1NsamAes2B
				BitFail,
				dde3000p01v1NsamAes2BTrapEnable
				AlarmEnable,
				dde3000p01v1PckAGr1B
				Bit0No1Yes,
				dde3000p01v1PckAGr2B
				Bit0No1Yes,
				dde3000p01v1PckAGr3B
				Bit0No1Yes,
				dde3000p01v1PckAGr4B
				Bit0No1Yes
			 }

		-- 1.3.6.1.4.1.10106.3.101291.1.1.1
		dde3000p01v1Index OBJECT-TYPE
			SYNTAX ModuleIndex
			MAX-ACCESS read-only
			STATUS current
			DESCRIPTION
				"Index of DDE3000P01V1 Table"
		::= { dde3000p01v1Entry 1 }

		-- 1.3.6.1.4.1.10106.3.101291.1.1.3
		dde3000p01v1OperatingMode OBJECT-TYPE
			SYNTAX BitEmbed1
			MAX-ACCESS read-write
			STATUS current
			DESCRIPTION
				"Allows selecting if the module acts as two one group deembedders or as one two groups deembedder"
		::= { dde3000p01v1Entry 3 }

		-- 1.3.6.1.4.1.10106.3.101291.1.1.5
		dde3000p01v1GroupA OBJECT-TYPE
			SYNTAX EmbedGroup
			MAX-ACCESS read-write
			STATUS current
			DESCRIPTION
				"Allows selecting the group from which the audio is deembedded"
		::= { dde3000p01v1Entry 5 }

		-- 1.3.6.1.4.1.10106.3.101291.1.1.6
		dde3000p01v1GroupATrapEnable OBJECT-TYPE
			SYNTAX AlarmEnable
			MAX-ACCESS read-write
			STATUS current
			DESCRIPTION
				"Allows selecting the group from which the audio is deembedded Trap Enable"
		::= { dde3000p01v1Entry 6 }

		-- 1.3.6.1.4.1.10106.3.101291.1.1.7
		dde3000p01v1GroupB OBJECT-TYPE
			SYNTAX EmbedGroup
			MAX-ACCESS read-write
			STATUS current
			DESCRIPTION
				"Allows selecting the group from which the audio is deembedded"
		::= { dde3000p01v1Entry 7 }

		-- 1.3.6.1.4.1.10106.3.101291.1.1.8
		dde3000p01v1GroupBTrapEnable OBJECT-TYPE
			SYNTAX AlarmEnable
			MAX-ACCESS read-write
			STATUS current
			DESCRIPTION
				"Allows selecting the group from which the audio is deembedded Trap Enable"
		::= { dde3000p01v1Entry 8 }

		-- 1.3.6.1.4.1.10106.3.101291.1.1.9
		dde3000p01v1ClnGr1A OBJECT-TYPE
			SYNTAX Bit0No1Yes
			MAX-ACCESS read-write
			STATUS current
			DESCRIPTION
				"Allows selecting if all the group 1 audio packets are deleted after deembedding"
		::= { dde3000p01v1Entry 9 }

		-- 1.3.6.1.4.1.10106.3.101291.1.1.11
		dde3000p01v1ClnGr2A OBJECT-TYPE
			SYNTAX Bit0No1Yes
			MAX-ACCESS read-write
			STATUS current
			DESCRIPTION
				"Allows selecting if all the group 2 audio packets are deleted after deembedding"
		::= { dde3000p01v1Entry 11 }

		-- 1.3.6.1.4.1.10106.3.101291.1.1.13
		dde3000p01v1ClnGr3A OBJECT-TYPE
			SYNTAX Bit0No1Yes
			MAX-ACCESS read-write
			STATUS current
			DESCRIPTION
				"Allows selecting if all the group 3 audio packets are deleted after deembedding"
		::= { dde3000p01v1Entry 13 }

		-- 1.3.6.1.4.1.10106.3.101291.1.1.15
		dde3000p01v1ClnGr4A OBJECT-TYPE
			SYNTAX Bit0No1Yes
			MAX-ACCESS read-write
			STATUS current
			DESCRIPTION
				"Allows selecting if all the group 4 audio packets are deleted after deembedding"
		::= { dde3000p01v1Entry 15 }

		-- 1.3.6.1.4.1.10106.3.101291.1.1.17
		dde3000p01v1ClnGr1B OBJECT-TYPE
			SYNTAX Bit0No1Yes
			MAX-ACCESS read-write
			STATUS current
			DESCRIPTION
				"Allows selecting if all the group 1 audio packets are deleted after deembedding"
		::= { dde3000p01v1Entry 17 }

		-- 1.3.6.1.4.1.10106.3.101291.1.1.19
		dde3000p01v1ClnGr2B OBJECT-TYPE
			SYNTAX Bit0No1Yes
			MAX-ACCESS read-write
			STATUS current
			DESCRIPTION
				"Allows selecting if all the group 2 audio packets are deleted after deembedding"
		::= { dde3000p01v1Entry 19 }

		-- 1.3.6.1.4.1.10106.3.101291.1.1.21
		dde3000p01v1ClnGr3B OBJECT-TYPE
			SYNTAX Bit0No1Yes
			MAX-ACCESS read-write
			STATUS current
			DESCRIPTION
				"Allows selecting if all the group 3 audio packets are deleted after deembedding"
		::= { dde3000p01v1Entry 21 }

		-- 1.3.6.1.4.1.10106.3.101291.1.1.23
		dde3000p01v1ClnGr4B OBJECT-TYPE
			SYNTAX Bit0No1Yes
			MAX-ACCESS read-write
			STATUS current
			DESCRIPTION
				"Allows selecting if all the group 4 audio packets are deleted after deembedding"
		::= { dde3000p01v1Entry 23 }

		-- 1.3.6.1.4.1.10106.3.101291.1.1.25
		dde3000p01v1MuteAes1A OBJECT-TYPE
			SYNTAX Bit0No1Yes
			MAX-ACCESS read-write
			STATUS current
			DESCRIPTION
				"Allows muting of both AES1 channels"
		::= { dde3000p01v1Entry 25 }

		-- 1.3.6.1.4.1.10106.3.101291.1.1.27
		dde3000p01v1PhInvAes1A OBJECT-TYPE
			SYNTAX Bit0No1Yes
			MAX-ACCESS read-write
			STATUS current
			DESCRIPTION
				"Allows inverting the phase of one AES1 channel"
		::= { dde3000p01v1Entry 27 }

		-- 1.3.6.1.4.1.10106.3.101291.1.1.29
		dde3000p01v1SwapAes1A OBJECT-TYPE
			SYNTAX Bit0No1Yes
			MAX-ACCESS read-write
			STATUS current
			DESCRIPTION
				"Allows swapping AES1 channels"
		::= { dde3000p01v1Entry 29 }

		-- 1.3.6.1.4.1.10106.3.101291.1.1.31
		dde3000p01v1MuteAes2A OBJECT-TYPE
			SYNTAX Bit0No1Yes
			MAX-ACCESS read-write
			STATUS current
			DESCRIPTION
				"Allows muting of both AES2 channels"
		::= { dde3000p01v1Entry 31 }

		-- 1.3.6.1.4.1.10106.3.101291.1.1.33
		dde3000p01v1PhInvAes2A OBJECT-TYPE
			SYNTAX Bit0No1Yes
			MAX-ACCESS read-write
			STATUS current
			DESCRIPTION
				"Allows inverting the phase of one AES2 channel"
		::= { dde3000p01v1Entry 33 }

		-- 1.3.6.1.4.1.10106.3.101291.1.1.35
		dde3000p01v1SwapAes2A OBJECT-TYPE
			SYNTAX Bit0No1Yes
			MAX-ACCESS read-write
			STATUS current
			DESCRIPTION
				"Allows swapping AES2 channels"
		::= { dde3000p01v1Entry 35 }

		-- 1.3.6.1.4.1.10106.3.101291.1.1.37
		dde3000p01v1SwapAesA OBJECT-TYPE
			SYNTAX Bit0No1Yes
			MAX-ACCESS read-write
			STATUS current
			DESCRIPTION
				"Allows swapping AES1 and AES2 frames"
		::= { dde3000p01v1Entry 37 }

		-- 1.3.6.1.4.1.10106.3.101291.1.1.39
		dde3000p01v1MuteAes1B OBJECT-TYPE
			SYNTAX Bit0No1Yes
			MAX-ACCESS read-write
			STATUS current
			DESCRIPTION
				"Allows muting of both AES1 channels"
		::= { dde3000p01v1Entry 39 }

		-- 1.3.6.1.4.1.10106.3.101291.1.1.41
		dde3000p01v1PhInvAes1B OBJECT-TYPE
			SYNTAX Bit0No1Yes
			MAX-ACCESS read-write
			STATUS current
			DESCRIPTION
				"Allows inverting the phase of one AES1 channel"
		::= { dde3000p01v1Entry 41 }

		-- 1.3.6.1.4.1.10106.3.101291.1.1.43
		dde3000p01v1SwapAes1B OBJECT-TYPE
			SYNTAX Bit0No1Yes
			MAX-ACCESS read-write
			STATUS current
			DESCRIPTION
				"Allows swapping AES1 channels"
		::= { dde3000p01v1Entry 43 }

		-- 1.3.6.1.4.1.10106.3.101291.1.1.45
		dde3000p01v1MuteAes2B OBJECT-TYPE
			SYNTAX Bit0No1Yes
			MAX-ACCESS read-write
			STATUS current
			DESCRIPTION
				"Allows muting of both AES2 channels"
		::= { dde3000p01v1Entry 45 }

		-- 1.3.6.1.4.1.10106.3.101291.1.1.47
		dde3000p01v1PhInvAes2B OBJECT-TYPE
			SYNTAX Bit0No1Yes
			MAX-ACCESS read-write
			STATUS current
			DESCRIPTION
				"Allows inverting the phase of one AES2 channel"
		::= { dde3000p01v1Entry 47 }

		-- 1.3.6.1.4.1.10106.3.101291.1.1.49
		dde3000p01v1SwapAes2B OBJECT-TYPE
			SYNTAX Bit0No1Yes
			MAX-ACCESS read-write
			STATUS current
			DESCRIPTION
				"Allows swapping AES2 channels"
		::= { dde3000p01v1Entry 49 }

		-- 1.3.6.1.4.1.10106.3.101291.1.1.51
		dde3000p01v1SwapAesB OBJECT-TYPE
			SYNTAX Bit0No1Yes
			MAX-ACCESS read-write
			STATUS current
			DESCRIPTION
				"Allows swapping AES1 and AES2 frames"
		::= { dde3000p01v1Entry 51 }

		-- 1.3.6.1.4.1.10106.3.101291.1.1.53
		dde3000p01v1NoSignalA OBJECT-TYPE
			SYNTAX BitFail
			MAX-ACCESS read-only
			STATUS current
			DESCRIPTION
				"SDI input signal status"
		::= { dde3000p01v1Entry 53 }

		-- 1.3.6.1.4.1.10106.3.101291.1.1.54
		dde3000p01v1NoSignalATrapEnable OBJECT-TYPE
			SYNTAX AlarmEnable
			MAX-ACCESS read-write
			STATUS current
			DESCRIPTION
				"SDI input signal status Trap Enable"
		::= { dde3000p01v1Entry 54 }

		-- 1.3.6.1.4.1.10106.3.101291.1.1.55
		dde3000p01v1NsamAes1A OBJECT-TYPE
			SYNTAX BitFail
			MAX-ACCESS read-only
			STATUS current
			DESCRIPTION
				"Bad number of samples per frame in AES1 signal"
		::= { dde3000p01v1Entry 55 }

		-- 1.3.6.1.4.1.10106.3.101291.1.1.56
		dde3000p01v1NsamAes1ATrapEnable OBJECT-TYPE
			SYNTAX AlarmEnable
			MAX-ACCESS read-write
			STATUS current
			DESCRIPTION
				"Bad number of samples per frame in AES1 signal Trap Enable"
		::= { dde3000p01v1Entry 56 }

		-- 1.3.6.1.4.1.10106.3.101291.1.1.57
		dde3000p01v1NsamAes2A OBJECT-TYPE
			SYNTAX BitFail
			MAX-ACCESS read-only
			STATUS current
			DESCRIPTION
				"Bad number of samples per frame in AES2 signal"
		::= { dde3000p01v1Entry 57 }

		-- 1.3.6.1.4.1.10106.3.101291.1.1.58
		dde3000p01v1NsamAes2ATrapEnable OBJECT-TYPE
			SYNTAX AlarmEnable
			MAX-ACCESS read-write
			STATUS current
			DESCRIPTION
				"Bad number of samples per frame in AES2 signal Trap Enable"
		::= { dde3000p01v1Entry 58 }

		-- 1.3.6.1.4.1.10106.3.101291.1.1.59
		dde3000p01v1PckAGr1A OBJECT-TYPE
			SYNTAX Bit0No1Yes
			MAX-ACCESS read-only
			STATUS current
			DESCRIPTION
				"Group 1 normal audio packets (20 bits) detected"
		::= { dde3000p01v1Entry 59 }

		-- 1.3.6.1.4.1.10106.3.101291.1.1.61
		dde3000p01v1PckAGr2A OBJECT-TYPE
			SYNTAX Bit0No1Yes
			MAX-ACCESS read-only
			STATUS current
			DESCRIPTION
				"Group 2 normal audio packets (20 bits) detected"
		::= { dde3000p01v1Entry 61 }

		-- 1.3.6.1.4.1.10106.3.101291.1.1.63
		dde3000p01v1PckAGr3A OBJECT-TYPE
			SYNTAX Bit0No1Yes
			MAX-ACCESS read-only
			STATUS current
			DESCRIPTION
				"Group 3 normal audio packets (20 bits) detected"
		::= { dde3000p01v1Entry 63 }

		-- 1.3.6.1.4.1.10106.3.101291.1.1.65
		dde3000p01v1PckAGr4A OBJECT-TYPE
			SYNTAX Bit0No1Yes
			MAX-ACCESS read-only
			STATUS current
			DESCRIPTION
				"Group 4 normal audio packets (20 bits) detected"
		::= { dde3000p01v1Entry 65 }

		-- 1.3.6.1.4.1.10106.3.101291.1.1.67
		dde3000p01v1NoSignalB OBJECT-TYPE
			SYNTAX BitFail
			MAX-ACCESS read-only
			STATUS current
			DESCRIPTION
				"SDI input signal status"
		::= { dde3000p01v1Entry 67 }

		-- 1.3.6.1.4.1.10106.3.101291.1.1.68
		dde3000p01v1NoSignalBTrapEnable OBJECT-TYPE
			SYNTAX AlarmEnable
			MAX-ACCESS read-write
			STATUS current
			DESCRIPTION
				"SDI input signal status Trap Enable"
		::= { dde3000p01v1Entry 68 }

		-- 1.3.6.1.4.1.10106.3.101291.1.1.69
		dde3000p01v1NsamAes1B OBJECT-TYPE
			SYNTAX BitFail
			MAX-ACCESS read-only
			STATUS current
			DESCRIPTION
				"Bad number of samples per frame in AES1 signal"
		::= { dde3000p01v1Entry 69 }

		-- 1.3.6.1.4.1.10106.3.101291.1.1.70
		dde3000p01v1NsamAes1BTrapEnable OBJECT-TYPE
			SYNTAX AlarmEnable
			MAX-ACCESS read-write
			STATUS current
			DESCRIPTION
				"Bad number of samples per frame in AES1 signal Trap Enable"
		::= { dde3000p01v1Entry 70 }

		-- 1.3.6.1.4.1.10106.3.101291.1.1.71
		dde3000p01v1NsamAes2B OBJECT-TYPE
			SYNTAX BitFail
			MAX-ACCESS read-only
			STATUS current
			DESCRIPTION
				"Bad number of samples per frame in AES2 signal"
		::= { dde3000p01v1Entry 71 }

		-- 1.3.6.1.4.1.10106.3.101291.1.1.72
		dde3000p01v1NsamAes2BTrapEnable OBJECT-TYPE
			SYNTAX AlarmEnable
			MAX-ACCESS read-write
			STATUS current
			DESCRIPTION
				"Bad number of samples per frame in AES2 signal Trap Enable"
		::= { dde3000p01v1Entry 72 }

		-- 1.3.6.1.4.1.10106.3.101291.1.1.73
		dde3000p01v1PckAGr1B OBJECT-TYPE
			SYNTAX Bit0No1Yes
			MAX-ACCESS read-only
			STATUS current
			DESCRIPTION
				"Group 1 normal audio packets (20 bits) detected"
		::= { dde3000p01v1Entry 73 }

		-- 1.3.6.1.4.1.10106.3.101291.1.1.75
		dde3000p01v1PckAGr2B OBJECT-TYPE
			SYNTAX Bit0No1Yes
			MAX-ACCESS read-only
			STATUS current
			DESCRIPTION
				"Group 2 normal audio packets (20 bits) detected"
		::= { dde3000p01v1Entry 75 }

		-- 1.3.6.1.4.1.10106.3.101291.1.1.77
		dde3000p01v1PckAGr3B OBJECT-TYPE
			SYNTAX Bit0No1Yes
			MAX-ACCESS read-only
			STATUS current
			DESCRIPTION
				"Group 3 normal audio packets (20 bits) detected"
		::= { dde3000p01v1Entry 77 }

		-- 1.3.6.1.4.1.10106.3.101291.1.1.79
		dde3000p01v1PckAGr4B OBJECT-TYPE
			SYNTAX Bit0No1Yes
			MAX-ACCESS read-only
			STATUS current
			DESCRIPTION
				"Group 4 normal audio packets (20 bits) detected"
		::= { dde3000p01v1Entry 79 }

		-- 1.3.6.1.4.1.10106.3.137701
		avp0621p01v1 OBJECT IDENTIFIER ::= { albalaProducts 137701 }

		-- 1.3.6.1.4.1.10106.3.137701.1
		avp0621p01v1Table  OBJECT-TYPE
			SYNTAX SEQUENCE OF Avp0621p01v1Entry
			MAX-ACCESS not-accessible
			STATUS current
			DESCRIPTION
				"Module  AVP0621P01V1 Table"
			::= { avp0621p01v1 1 }

		-- 1.3.6.1.4.1.10106.3.137701.1.1
		avp0621p01v1Entry  OBJECT-TYPE
			SYNTAX Avp0621p01v1Entry
			MAX-ACCESS not-accessible
			STATUS current
			DESCRIPTION
				"Module AVP0621P01V1 Entry"
			INDEX { avp0621p01v1Index }
			::= { avp0621p01v1Table 1 }

			Avp0621p01v1Entry ::=
			SEQUENCE {
				avp0621p01v1Index
				ModuleIndex,
				avp0621p01v1Output1
				Inputs06,
				avp0621p01v1SwitchMode
				PreselSwMode1,
				avp0621p01v1SwitchTime
				PreselSwTime1,
				avp0621p01v1NoSync
				BitFail,
				avp0621p01v1SyncLines
				Bit06251525,
				avp0621p01v1SyncType
				Bit0Fld1Fra
			 }

		-- 1.3.6.1.4.1.10106.3.101291.1.1.1
		avp0621p01v1Index OBJECT-TYPE
			SYNTAX ModuleIndex
			MAX-ACCESS read-only
			STATUS current
			DESCRIPTION
				"Index of AVP0621P01V1 Table"
		::= { avp0621p01v1Entry 1 }

		-- 1.3.6.1.4.1.10106.3.101291.1.1.3
		avp0621p01v1Output1 OBJECT-TYPE
			SYNTAX Inputs06
			MAX-ACCESS read-write
			STATUS current
			DESCRIPTION
				"Input routed to output 1"
		::= { avp0621p01v1Entry 3 }

		-- 1.3.6.1.4.1.10106.3.101291.1.1.5
		avp0621p01v1SwitchMode OBJECT-TYPE
			SYNTAX PreselSwMode1
			MAX-ACCESS read-write
			STATUS current
			DESCRIPTION
				"Allows selection switching mode: master or follow another module"
		::= { avp0621p01v1Entry 5 }

		-- 1.3.6.1.4.1.10106.3.101291.1.1.7
		avp0621p01v1SwitchTime OBJECT-TYPE
			SYNTAX PreselSwTime1
			MAX-ACCESS read-write
			STATUS current
			DESCRIPTION
				"Allows selection of switching time"
		::= { avp0621p01v1Entry 7 }

		-- 1.3.6.1.4.1.10106.3.101291.1.1.9
		avp0621p01v1NoSync OBJECT-TYPE
			SYNTAX BitFail
			MAX-ACCESS read-only
			STATUS current
			DESCRIPTION
				"Sync presence status"
		::= { avp0621p01v1Entry 9 }

		-- 1.3.6.1.4.1.10106.3.101291.1.1.11
		avp0621p01v1SyncLines OBJECT-TYPE
			SYNTAX Bit06251525
			MAX-ACCESS read-only
			STATUS current
			DESCRIPTION
				"Number of lines of sync signal"
		::= { avp0621p01v1Entry 11 }

		-- 1.3.6.1.4.1.10106.3.101291.1.1.13
		avp0621p01v1SyncType OBJECT-TYPE
			SYNTAX Bit0Fld1Fra
			MAX-ACCESS read-only
			STATUS current
			DESCRIPTION
				"Type of sync signal"
		::= { avp0621p01v1Entry 13 }

		-- 1.3.6.1.4.1.10106.3.139701
		aad3034p01v1 OBJECT IDENTIFIER ::= { albalaProducts 139701 }

		-- 1.3.6.1.4.1.10106.3.139701.1
		aad3034p01v1Table  OBJECT-TYPE
			SYNTAX SEQUENCE OF Aad3034p01v1Entry
			MAX-ACCESS not-accessible
			STATUS current
			DESCRIPTION
				"Module  AAD3034P01V1 Table"
			::= { aad3034p01v1 1 }

		-- 1.3.6.1.4.1.10106.3.139701.1.1
		aad3034p01v1Entry  OBJECT-TYPE
			SYNTAX Aad3034p01v1Entry
			MAX-ACCESS not-accessible
			STATUS current
			DESCRIPTION
				"Module AAD3034P01V1 Entry"
			INDEX { aad3034p01v1Index }
			::= { aad3034p01v1Table 1 }

			Aad3034p01v1Entry ::=
			SEQUENCE {
				aad3034p01v1Index
				ModuleIndex,
				aad3034p01v1GainRA
				GainDb1,
				aad3034p01v1GainLA
				GainDb1,
				aad3034p01v1GainRB
				GainDb1,
				aad3034p01v1GainLB
				GainDb1,
				aad3034p01v1GainRRlA
				GainDb2,
				aad3034p01v1GainLRlA
				GainDb2,
				aad3034p01v1GainRRlB
				GainDb2,
				aad3034p01v1GainLRlB
				GainDb2,
				aad3034p01v1NoSigTout
				TimeS2,
				aad3034p01v1SilThrLevel
				LevelDbuD5,
				aad3034p01v1OvlThrLevel
				LevelDbuD5,
				aad3034p01v1SilenceRA
				BitFail,
				aad3034p01v1SilenceRATrapEnable
				AlarmEnable,
				aad3034p01v1SilenceLA
				BitFail,
				aad3034p01v1SilenceLATrapEnable
				AlarmEnable,
				aad3034p01v1AntiphaseA
				BitFail,
				aad3034p01v1AntiphaseATrapEnable
				AlarmEnable,
				aad3034p01v1OverloadRA
				BitFail,
				aad3034p01v1OverloadRATrapEnable
				AlarmEnable,
				aad3034p01v1OverloadLA
				BitFail,
				aad3034p01v1OverloadLATrapEnable
				AlarmEnable,
				aad3034p01v1OverloadRlA
				BitFail,
				aad3034p01v1OverloadRlATrapEnable
				AlarmEnable,
				aad3034p01v1SilenceRB
				BitFail,
				aad3034p01v1SilenceRBTrapEnable
				AlarmEnable,
				aad3034p01v1SilenceLB
				BitFail,
				aad3034p01v1SilenceLBTrapEnable
				AlarmEnable,
				aad3034p01v1AntiphaseB
				BitFail,
				aad3034p01v1AntiphaseBTrapEnable
				AlarmEnable,
				aad3034p01v1OverloadRB
				BitFail,
				aad3034p01v1OverloadRBTrapEnable
				AlarmEnable,
				aad3034p01v1OverloadLB
				BitFail,
				aad3034p01v1OverloadLBTrapEnable
				AlarmEnable,
				aad3034p01v1OverloadRlB
				BitFail,
				aad3034p01v1OverloadRlBTrapEnable
				AlarmEnable,
				aad3034p01v1LevelRA
				LevelDbuD5,
				aad3034p01v1LevelLA
				LevelDbuD5,
				aad3034p01v1LevelRB
				LevelDbuD5,
				aad3034p01v1LevelLB
				LevelDbuD5
			 }

		-- 1.3.6.1.4.1.10106.3.101291.1.1.1
		aad3034p01v1Index OBJECT-TYPE
			SYNTAX ModuleIndex
			MAX-ACCESS read-only
			STATUS current
			DESCRIPTION
				"Index of AAD3034P01V1 Table"
		::= { aad3034p01v1Entry 1 }

		-- 1.3.6.1.4.1.10106.3.101291.1.1.3
		aad3034p01v1GainRA OBJECT-TYPE
			SYNTAX GainDb1
			MAX-ACCESS read-write
			STATUS current
			DESCRIPTION
				"Gain right channel"
		::= { aad3034p01v1Entry 3 }

		-- 1.3.6.1.4.1.10106.3.101291.1.1.5
		aad3034p01v1GainLA OBJECT-TYPE
			SYNTAX GainDb1
			MAX-ACCESS read-write
			STATUS current
			DESCRIPTION
				"Gain left channel"
		::= { aad3034p01v1Entry 5 }

		-- 1.3.6.1.4.1.10106.3.101291.1.1.7
		aad3034p01v1GainRB OBJECT-TYPE
			SYNTAX GainDb1
			MAX-ACCESS read-write
			STATUS current
			DESCRIPTION
				"Gain right channel"
		::= { aad3034p01v1Entry 7 }

		-- 1.3.6.1.4.1.10106.3.101291.1.1.9
		aad3034p01v1GainLB OBJECT-TYPE
			SYNTAX GainDb1
			MAX-ACCESS read-write
			STATUS current
			DESCRIPTION
				"Gain left channel"
		::= { aad3034p01v1Entry 9 }

		-- 1.3.6.1.4.1.10106.3.101291.1.1.11
		aad3034p01v1GainRRlA OBJECT-TYPE
			SYNTAX GainDb2
			MAX-ACCESS read-write
			STATUS current
			DESCRIPTION
				"Gain right in right+left channel"
		::= { aad3034p01v1Entry 11 }

		-- 1.3.6.1.4.1.10106.3.101291.1.1.13
		aad3034p01v1GainLRlA OBJECT-TYPE
			SYNTAX GainDb2
			MAX-ACCESS read-write
			STATUS current
			DESCRIPTION
				"Gain left in right+left channel"
		::= { aad3034p01v1Entry 13 }

		-- 1.3.6.1.4.1.10106.3.101291.1.1.15
		aad3034p01v1GainRRlB OBJECT-TYPE
			SYNTAX GainDb2
			MAX-ACCESS read-write
			STATUS current
			DESCRIPTION
				"Gain right in right+left channel"
		::= { aad3034p01v1Entry 15 }

		-- 1.3.6.1.4.1.10106.3.101291.1.1.17
		aad3034p01v1GainLRlB OBJECT-TYPE
			SYNTAX GainDb2
			MAX-ACCESS read-write
			STATUS current
			DESCRIPTION
				"Gain left in right+left channel"
		::= { aad3034p01v1Entry 17 }

		-- 1.3.6.1.4.1.10106.3.101291.1.1.19
		aad3034p01v1NoSigTout OBJECT-TYPE
			SYNTAX TimeS2
			MAX-ACCESS read-write
			STATUS current
			DESCRIPTION
				"Silence timeout"
		::= { aad3034p01v1Entry 19 }

		-- 1.3.6.1.4.1.10106.3.101291.1.1.21
		aad3034p01v1SilThrLevel OBJECT-TYPE
			SYNTAX LevelDbuD5
			MAX-ACCESS read-write
			STATUS current
			DESCRIPTION
				"Silence threshold level"
		::= { aad3034p01v1Entry 21 }

		-- 1.3.6.1.4.1.10106.3.101291.1.1.23
		aad3034p01v1OvlThrLevel OBJECT-TYPE
			SYNTAX LevelDbuD5
			MAX-ACCESS read-write
			STATUS current
			DESCRIPTION
				"Overload threshold level"
		::= { aad3034p01v1Entry 23 }

		-- 1.3.6.1.4.1.10106.3.101291.1.1.25
		aad3034p01v1SilenceRA OBJECT-TYPE
			SYNTAX BitFail
			MAX-ACCESS read-only
			STATUS current
			DESCRIPTION
				"Right channel silence fail"
		::= { aad3034p01v1Entry 25 }

		-- 1.3.6.1.4.1.10106.3.101291.1.1.26
		aad3034p01v1SilenceRATrapEnable OBJECT-TYPE
			SYNTAX AlarmEnable
			MAX-ACCESS read-write
			STATUS current
			DESCRIPTION
				"Right channel silence fail Trap Enable"
		::= { aad3034p01v1Entry 26 }

		-- 1.3.6.1.4.1.10106.3.101291.1.1.27
		aad3034p01v1SilenceLA OBJECT-TYPE
			SYNTAX BitFail
			MAX-ACCESS read-only
			STATUS current
			DESCRIPTION
				"Left channel silence fail"
		::= { aad3034p01v1Entry 27 }

		-- 1.3.6.1.4.1.10106.3.101291.1.1.28
		aad3034p01v1SilenceLATrapEnable OBJECT-TYPE
			SYNTAX AlarmEnable
			MAX-ACCESS read-write
			STATUS current
			DESCRIPTION
				"Left channel silence fail Trap Enable"
		::= { aad3034p01v1Entry 28 }

		-- 1.3.6.1.4.1.10106.3.101291.1.1.29
		aad3034p01v1AntiphaseA OBJECT-TYPE
			SYNTAX BitFail
			MAX-ACCESS read-only
			STATUS current
			DESCRIPTION
				"Antiphase fail"
		::= { aad3034p01v1Entry 29 }

		-- 1.3.6.1.4.1.10106.3.101291.1.1.30
		aad3034p01v1AntiphaseATrapEnable OBJECT-TYPE
			SYNTAX AlarmEnable
			MAX-ACCESS read-write
			STATUS current
			DESCRIPTION
				"Antiphase fail Trap Enable"
		::= { aad3034p01v1Entry 30 }

		-- 1.3.6.1.4.1.10106.3.101291.1.1.31
		aad3034p01v1OverloadRA OBJECT-TYPE
			SYNTAX BitFail
			MAX-ACCESS read-only
			STATUS current
			DESCRIPTION
				"Right channel overload fail"
		::= { aad3034p01v1Entry 31 }

		-- 1.3.6.1.4.1.10106.3.101291.1.1.32
		aad3034p01v1OverloadRATrapEnable OBJECT-TYPE
			SYNTAX AlarmEnable
			MAX-ACCESS read-write
			STATUS current
			DESCRIPTION
				"Right channel overload fail Trap Enable"
		::= { aad3034p01v1Entry 32 }

		-- 1.3.6.1.4.1.10106.3.101291.1.1.33
		aad3034p01v1OverloadLA OBJECT-TYPE
			SYNTAX BitFail
			MAX-ACCESS read-only
			STATUS current
			DESCRIPTION
				"Left channel overload fail"
		::= { aad3034p01v1Entry 33 }

		-- 1.3.6.1.4.1.10106.3.101291.1.1.34
		aad3034p01v1OverloadLATrapEnable OBJECT-TYPE
			SYNTAX AlarmEnable
			MAX-ACCESS read-write
			STATUS current
			DESCRIPTION
				"Left channel overload fail Trap Enable"
		::= { aad3034p01v1Entry 34 }

		-- 1.3.6.1.4.1.10106.3.101291.1.1.35
		aad3034p01v1OverloadRlA OBJECT-TYPE
			SYNTAX BitFail
			MAX-ACCESS read-only
			STATUS current
			DESCRIPTION
				"Right+left channel overload fail"
		::= { aad3034p01v1Entry 35 }

		-- 1.3.6.1.4.1.10106.3.101291.1.1.36
		aad3034p01v1OverloadRlATrapEnable OBJECT-TYPE
			SYNTAX AlarmEnable
			MAX-ACCESS read-write
			STATUS current
			DESCRIPTION
				"Right+left channel overload fail Trap Enable"
		::= { aad3034p01v1Entry 36 }

		-- 1.3.6.1.4.1.10106.3.101291.1.1.37
		aad3034p01v1SilenceRB OBJECT-TYPE
			SYNTAX BitFail
			MAX-ACCESS read-only
			STATUS current
			DESCRIPTION
				"Right channel silence fail"
		::= { aad3034p01v1Entry 37 }

		-- 1.3.6.1.4.1.10106.3.101291.1.1.38
		aad3034p01v1SilenceRBTrapEnable OBJECT-TYPE
			SYNTAX AlarmEnable
			MAX-ACCESS read-write
			STATUS current
			DESCRIPTION
				"Right channel silence fail Trap Enable"
		::= { aad3034p01v1Entry 38 }

		-- 1.3.6.1.4.1.10106.3.101291.1.1.39
		aad3034p01v1SilenceLB OBJECT-TYPE
			SYNTAX BitFail
			MAX-ACCESS read-only
			STATUS current
			DESCRIPTION
				"Left channel silence fail"
		::= { aad3034p01v1Entry 39 }

		-- 1.3.6.1.4.1.10106.3.101291.1.1.40
		aad3034p01v1SilenceLBTrapEnable OBJECT-TYPE
			SYNTAX AlarmEnable
			MAX-ACCESS read-write
			STATUS current
			DESCRIPTION
				"Left channel silence fail Trap Enable"
		::= { aad3034p01v1Entry 40 }

		-- 1.3.6.1.4.1.10106.3.101291.1.1.41
		aad3034p01v1AntiphaseB OBJECT-TYPE
			SYNTAX BitFail
			MAX-ACCESS read-only
			STATUS current
			DESCRIPTION
				"Antiphase fail"
		::= { aad3034p01v1Entry 41 }

		-- 1.3.6.1.4.1.10106.3.101291.1.1.42
		aad3034p01v1AntiphaseBTrapEnable OBJECT-TYPE
			SYNTAX AlarmEnable
			MAX-ACCESS read-write
			STATUS current
			DESCRIPTION
				"Antiphase fail Trap Enable"
		::= { aad3034p01v1Entry 42 }

		-- 1.3.6.1.4.1.10106.3.101291.1.1.43
		aad3034p01v1OverloadRB OBJECT-TYPE
			SYNTAX BitFail
			MAX-ACCESS read-only
			STATUS current
			DESCRIPTION
				"Right channel overload fail"
		::= { aad3034p01v1Entry 43 }

		-- 1.3.6.1.4.1.10106.3.101291.1.1.44
		aad3034p01v1OverloadRBTrapEnable OBJECT-TYPE
			SYNTAX AlarmEnable
			MAX-ACCESS read-write
			STATUS current
			DESCRIPTION
				"Right channel overload fail Trap Enable"
		::= { aad3034p01v1Entry 44 }

		-- 1.3.6.1.4.1.10106.3.101291.1.1.45
		aad3034p01v1OverloadLB OBJECT-TYPE
			SYNTAX BitFail
			MAX-ACCESS read-only
			STATUS current
			DESCRIPTION
				"Left channel overload fail"
		::= { aad3034p01v1Entry 45 }

		-- 1.3.6.1.4.1.10106.3.101291.1.1.46
		aad3034p01v1OverloadLBTrapEnable OBJECT-TYPE
			SYNTAX AlarmEnable
			MAX-ACCESS read-write
			STATUS current
			DESCRIPTION
				"Left channel overload fail Trap Enable"
		::= { aad3034p01v1Entry 46 }

		-- 1.3.6.1.4.1.10106.3.101291.1.1.47
		aad3034p01v1OverloadRlB OBJECT-TYPE
			SYNTAX BitFail
			MAX-ACCESS read-only
			STATUS current
			DESCRIPTION
				"Right+left channel overload fail"
		::= { aad3034p01v1Entry 47 }

		-- 1.3.6.1.4.1.10106.3.101291.1.1.48
		aad3034p01v1OverloadRlBTrapEnable OBJECT-TYPE
			SYNTAX AlarmEnable
			MAX-ACCESS read-write
			STATUS current
			DESCRIPTION
				"Right+left channel overload fail Trap Enable"
		::= { aad3034p01v1Entry 48 }

		-- 1.3.6.1.4.1.10106.3.101291.1.1.49
		aad3034p01v1LevelRA OBJECT-TYPE
			SYNTAX LevelDbuD5
			MAX-ACCESS read-only
			STATUS current
			DESCRIPTION
				"Right channel level"
		::= { aad3034p01v1Entry 49 }

		-- 1.3.6.1.4.1.10106.3.101291.1.1.51
		aad3034p01v1LevelLA OBJECT-TYPE
			SYNTAX LevelDbuD5
			MAX-ACCESS read-only
			STATUS current
			DESCRIPTION
				"Left channel level"
		::= { aad3034p01v1Entry 51 }

		-- 1.3.6.1.4.1.10106.3.101291.1.1.53
		aad3034p01v1LevelRB OBJECT-TYPE
			SYNTAX LevelDbuD5
			MAX-ACCESS read-only
			STATUS current
			DESCRIPTION
				"Right channel level"
		::= { aad3034p01v1Entry 53 }

		-- 1.3.6.1.4.1.10106.3.101291.1.1.55
		aad3034p01v1LevelLB OBJECT-TYPE
			SYNTAX LevelDbuD5
			MAX-ACCESS read-only
			STATUS current
			DESCRIPTION
				"Left channel level"
		::= { aad3034p01v1Entry 55 }

		-- 1.3.6.1.4.1.10106.3.140401
		avp1221p01v1 OBJECT IDENTIFIER ::= { albalaProducts 140401 }

		-- 1.3.6.1.4.1.10106.3.140401.1
		avp1221p01v1Table  OBJECT-TYPE
			SYNTAX SEQUENCE OF Avp1221p01v1Entry
			MAX-ACCESS not-accessible
			STATUS current
			DESCRIPTION
				"Module  AVP1221P01V1 Table"
			::= { avp1221p01v1 1 }

		-- 1.3.6.1.4.1.10106.3.140401.1.1
		avp1221p01v1Entry  OBJECT-TYPE
			SYNTAX Avp1221p01v1Entry
			MAX-ACCESS not-accessible
			STATUS current
			DESCRIPTION
				"Module AVP1221P01V1 Entry"
			INDEX { avp1221p01v1Index }
			::= { avp1221p01v1Table 1 }

			Avp1221p01v1Entry ::=
			SEQUENCE {
				avp1221p01v1Index
				ModuleIndex,
				avp1221p01v1Output1
				Inputs012,
				avp1221p01v1SwitchMode
				PreselSwMode1,
				avp1221p01v1SwitchTime
				PreselSwTime1,
				avp1221p01v1NoSync
				BitFail,
				avp1221p01v1SyncLines
				Bit06251525,
				avp1221p01v1SyncType
				Bit0Fld1Fra
			 }

		-- 1.3.6.1.4.1.10106.3.101291.1.1.1
		avp1221p01v1Index OBJECT-TYPE
			SYNTAX ModuleIndex
			MAX-ACCESS read-only
			STATUS current
			DESCRIPTION
				"Index of AVP1221P01V1 Table"
		::= { avp1221p01v1Entry 1 }

		-- 1.3.6.1.4.1.10106.3.101291.1.1.3
		avp1221p01v1Output1 OBJECT-TYPE
			SYNTAX Inputs012
			MAX-ACCESS read-write
			STATUS current
			DESCRIPTION
				"Input routed to output 1"
		::= { avp1221p01v1Entry 3 }

		-- 1.3.6.1.4.1.10106.3.101291.1.1.5
		avp1221p01v1SwitchMode OBJECT-TYPE
			SYNTAX PreselSwMode1
			MAX-ACCESS read-write
			STATUS current
			DESCRIPTION
				"Allows selection switching mode: master or follow another module"
		::= { avp1221p01v1Entry 5 }

		-- 1.3.6.1.4.1.10106.3.101291.1.1.7
		avp1221p01v1SwitchTime OBJECT-TYPE
			SYNTAX PreselSwTime1
			MAX-ACCESS read-write
			STATUS current
			DESCRIPTION
				"Allows selection of switching time"
		::= { avp1221p01v1Entry 7 }

		-- 1.3.6.1.4.1.10106.3.101291.1.1.9
		avp1221p01v1NoSync OBJECT-TYPE
			SYNTAX BitFail
			MAX-ACCESS read-only
			STATUS current
			DESCRIPTION
				"Sync presence status"
		::= { avp1221p01v1Entry 9 }

		-- 1.3.6.1.4.1.10106.3.101291.1.1.11
		avp1221p01v1SyncLines OBJECT-TYPE
			SYNTAX Bit06251525
			MAX-ACCESS read-only
			STATUS current
			DESCRIPTION
				"Number of lines of sync signal"
		::= { avp1221p01v1Entry 11 }

		-- 1.3.6.1.4.1.10106.3.101291.1.1.13
		avp1221p01v1SyncType OBJECT-TYPE
			SYNTAX Bit0Fld1Fra
			MAX-ACCESS read-only
			STATUS current
			DESCRIPTION
				"Type of sync signal"
		::= { avp1221p01v1Entry 13 }

		-- 1.3.6.1.4.1.10106.3.140801
		aap1221p01v1 OBJECT IDENTIFIER ::= { albalaProducts 140801 }

		-- 1.3.6.1.4.1.10106.3.140801.1
		aap1221p01v1Table  OBJECT-TYPE
			SYNTAX SEQUENCE OF Aap1221p01v1Entry
			MAX-ACCESS not-accessible
			STATUS current
			DESCRIPTION
				"Module  AAP1221P01V1 Table"
			::= { aap1221p01v1 1 }

		-- 1.3.6.1.4.1.10106.3.140801.1.1
		aap1221p01v1Entry  OBJECT-TYPE
			SYNTAX Aap1221p01v1Entry
			MAX-ACCESS not-accessible
			STATUS current
			DESCRIPTION
				"Module AAP1221P01V1 Entry"
			INDEX { aap1221p01v1Index }
			::= { aap1221p01v1Table 1 }

			Aap1221p01v1Entry ::=
			SEQUENCE {
				aap1221p01v1Index
				ModuleIndex,
				aap1221p01v1Output1
				Inputs012,
				aap1221p01v1SwitchMode
				PreselSwMode1
			 }

		-- 1.3.6.1.4.1.10106.3.101291.1.1.1
		aap1221p01v1Index OBJECT-TYPE
			SYNTAX ModuleIndex
			MAX-ACCESS read-only
			STATUS current
			DESCRIPTION
				"Index of AAP1221P01V1 Table"
		::= { aap1221p01v1Entry 1 }

		-- 1.3.6.1.4.1.10106.3.101291.1.1.3
		aap1221p01v1Output1 OBJECT-TYPE
			SYNTAX Inputs012
			MAX-ACCESS read-write
			STATUS current
			DESCRIPTION
				"Input routed to output 1"
		::= { aap1221p01v1Entry 3 }

		-- 1.3.6.1.4.1.10106.3.101291.1.1.5
		aap1221p01v1SwitchMode OBJECT-TYPE
			SYNTAX PreselSwMode1
			MAX-ACCESS read-write
			STATUS current
			DESCRIPTION
				"Allows selection switching mode: master or follow another module"
		::= { aap1221p01v1Entry 5 }

		-- 1.3.6.1.4.1.10106.3.141201
		frs3000p01v1 OBJECT IDENTIFIER ::= { albalaProducts 141201 }

		-- 1.3.6.1.4.1.10106.3.141201.1
		frs3000p01v1Table  OBJECT-TYPE
			SYNTAX SEQUENCE OF Frs3000p01v1Entry
			MAX-ACCESS not-accessible
			STATUS current
			DESCRIPTION
				"Module  FRS3000P01V1 Table"
			::= { frs3000p01v1 1 }

		-- 1.3.6.1.4.1.10106.3.141201.1.1
		frs3000p01v1Entry  OBJECT-TYPE
			SYNTAX Frs3000p01v1Entry
			MAX-ACCESS not-accessible
			STATUS current
			DESCRIPTION
				"Module FRS3000P01V1 Entry"
			INDEX { frs3000p01v1Index }
			::= { frs3000p01v1Table 1 }

			Frs3000p01v1Entry ::=
			SEQUENCE {
				frs3000p01v1Index
				ModuleIndex,
				frs3000p01v1Lines
				Bit05251625,
				frs3000p01v1FailMode
				Bit0Fre1Blk,
				frs3000p01v1FreezeMode
				Bit0Fld1Fra,
				frs3000p01v1LumaFilter
				Bit0Flt1Not,
				frs3000p01v1OperMode
				Bit0Del1Syn,
				frs3000p01v1SubcarrMode
				Bit0Tra1Fix,
				frs3000p01v1SynchroMode
				Bit0Fra1Lin,
				frs3000p01v1HDelay
				DelayPixel1,
				frs3000p01v1HDelayFine
				DelayPixelD8,
				frs3000p01v1VDelay
				DelayLines1,
				frs3000p01v1LumaGain
				GainLin1,
				frs3000p01v1ChromaGain
				GainLin1,
				frs3000p01v1BlackOffset
				BlackOffset1,
				frs3000p01v1SubcarrOffset
				Sch1,
				frs3000p01v1NoRef
				BitFail,
				frs3000p01v1NoRefTrapEnable
				AlarmEnable,
				frs3000p01v1RefUnlock
				BitFail,
				frs3000p01v1RefUnlockTrapEnable
				AlarmEnable,
				frs3000p01v1NoSig
				BitFail,
				frs3000p01v1NoSigTrapEnable
				AlarmEnable,
				frs3000p01v1SubcarrUnlock
				BitFail,
				frs3000p01v1SubcarrUnlockTrapEnable
				AlarmEnable,
				frs3000p01v1EdhError
				BitFail,
				frs3000p01v1SdiFormat
				Bit05251625,
				frs3000p01v1RefFormat
				Bit05251625
			 }

		-- 1.3.6.1.4.1.10106.3.101291.1.1.1
		frs3000p01v1Index OBJECT-TYPE
			SYNTAX ModuleIndex
			MAX-ACCESS read-only
			STATUS current
			DESCRIPTION
				"Index of FRS3000P01V1 Table"
		::= { frs3000p01v1Entry 1 }

		-- 1.3.6.1.4.1.10106.3.101291.1.1.3
		frs3000p01v1Lines OBJECT-TYPE
			SYNTAX Bit05251625
			MAX-ACCESS read-write
			STATUS current
			DESCRIPTION
				"TV input signal line number"
		::= { frs3000p01v1Entry 3 }

		-- 1.3.6.1.4.1.10106.3.101291.1.1.5
		frs3000p01v1FailMode OBJECT-TYPE
			SYNTAX Bit0Fre1Blk
			MAX-ACCESS read-write
			STATUS current
			DESCRIPTION
				"Allows selecting the output video signal if the input fails"
		::= { frs3000p01v1Entry 5 }

		-- 1.3.6.1.4.1.10106.3.101291.1.1.7
		frs3000p01v1FreezeMode OBJECT-TYPE
			SYNTAX Bit0Fld1Fra
			MAX-ACCESS read-write
			STATUS current
			DESCRIPTION
				"Allows selecting freeze mode"
		::= { frs3000p01v1Entry 7 }

		-- 1.3.6.1.4.1.10106.3.101291.1.1.9
		frs3000p01v1LumaFilter OBJECT-TYPE
			SYNTAX Bit0Flt1Not
			MAX-ACCESS read-write
			STATUS current
			DESCRIPTION
				"Allows selecting luminance filter"
		::= { frs3000p01v1Entry 9 }

		-- 1.3.6.1.4.1.10106.3.101291.1.1.11
		frs3000p01v1OperMode OBJECT-TYPE
			SYNTAX Bit0Del1Syn
			MAX-ACCESS read-write
			STATUS current
			DESCRIPTION
				"Allows selecting the operating mode"
		::= { frs3000p01v1Entry 11 }

		-- 1.3.6.1.4.1.10106.3.101291.1.1.13
		frs3000p01v1SubcarrMode OBJECT-TYPE
			SYNTAX Bit0Tra1Fix
			MAX-ACCESS read-write
			STATUS current
			DESCRIPTION
				"Allow selecting the subcarrier generating mode"
		::= { frs3000p01v1Entry 13 }

		-- 1.3.6.1.4.1.10106.3.101291.1.1.15
		frs3000p01v1SynchroMode OBJECT-TYPE
			SYNTAX Bit0Fra1Lin
			MAX-ACCESS read-write
			STATUS current
			DESCRIPTION
				"Allows selecting the synchronizing mode"
		::= { frs3000p01v1Entry 15 }

		-- 1.3.6.1.4.1.10106.3.101291.1.1.17
		frs3000p01v1HDelay OBJECT-TYPE
			SYNTAX DelayPixel1
			MAX-ACCESS read-write
			STATUS current
			DESCRIPTION
				"Allows adjusting the video horizontal delay"
		::= { frs3000p01v1Entry 17 }

		-- 1.3.6.1.4.1.10106.3.101291.1.1.19
		frs3000p01v1HDelayFine OBJECT-TYPE
			SYNTAX DelayPixelD8
			MAX-ACCESS read-write
			STATUS current
			DESCRIPTION
				"Allows adjusting the video subpixel delay"
		::= { frs3000p01v1Entry 19 }

		-- 1.3.6.1.4.1.10106.3.101291.1.1.21
		frs3000p01v1VDelay OBJECT-TYPE
			SYNTAX DelayLines1
			MAX-ACCESS read-write
			STATUS current
			DESCRIPTION
				"Allows adjusting the video vertical delay"
		::= { frs3000p01v1Entry 21 }

		-- 1.3.6.1.4.1.10106.3.101291.1.1.23
		frs3000p01v1LumaGain OBJECT-TYPE
			SYNTAX GainLin1
			MAX-ACCESS read-write
			STATUS current
			DESCRIPTION
				"Allows adjusting the luma gain"
		::= { frs3000p01v1Entry 23 }

		-- 1.3.6.1.4.1.10106.3.101291.1.1.25
		frs3000p01v1ChromaGain OBJECT-TYPE
			SYNTAX GainLin1
			MAX-ACCESS read-write
			STATUS current
			DESCRIPTION
				"Allows adjusting the chorma gain"
		::= { frs3000p01v1Entry 25 }

		-- 1.3.6.1.4.1.10106.3.101291.1.1.27
		frs3000p01v1BlackOffset OBJECT-TYPE
			SYNTAX BlackOffset1
			MAX-ACCESS read-write
			STATUS current
			DESCRIPTION
				"Allows adjusting the black offset"
		::= { frs3000p01v1Entry 27 }

		-- 1.3.6.1.4.1.10106.3.101291.1.1.29
		frs3000p01v1SubcarrOffset OBJECT-TYPE
			SYNTAX Sch1
			MAX-ACCESS read-write
			STATUS current
			DESCRIPTION
				"Allows adjusting the Analog video SCH"
		::= { frs3000p01v1Entry 29 }

		-- 1.3.6.1.4.1.10106.3.101291.1.1.31
		frs3000p01v1NoRef OBJECT-TYPE
			SYNTAX BitFail
			MAX-ACCESS read-only
			STATUS current
			DESCRIPTION
				"Indicates reference signal fail"
		::= { frs3000p01v1Entry 31 }

		-- 1.3.6.1.4.1.10106.3.101291.1.1.32
		frs3000p01v1NoRefTrapEnable OBJECT-TYPE
			SYNTAX AlarmEnable
			MAX-ACCESS read-write
			STATUS current
			DESCRIPTION
				"Indicates reference signal fail Trap Enable"
		::= { frs3000p01v1Entry 32 }

		-- 1.3.6.1.4.1.10106.3.101291.1.1.33
		frs3000p01v1RefUnlock OBJECT-TYPE
			SYNTAX BitFail
			MAX-ACCESS read-only
			STATUS current
			DESCRIPTION
				"Indicates reference signal unlock fail"
		::= { frs3000p01v1Entry 33 }

		-- 1.3.6.1.4.1.10106.3.101291.1.1.34
		frs3000p01v1RefUnlockTrapEnable OBJECT-TYPE
			SYNTAX AlarmEnable
			MAX-ACCESS read-write
			STATUS current
			DESCRIPTION
				"Indicates reference signal unlock fail Trap Enable"
		::= { frs3000p01v1Entry 34 }

		-- 1.3.6.1.4.1.10106.3.101291.1.1.35
		frs3000p01v1NoSig OBJECT-TYPE
			SYNTAX BitFail
			MAX-ACCESS read-only
			STATUS current
			DESCRIPTION
				"Indicates SDI signal fail"
		::= { frs3000p01v1Entry 35 }

		-- 1.3.6.1.4.1.10106.3.101291.1.1.36
		frs3000p01v1NoSigTrapEnable OBJECT-TYPE
			SYNTAX AlarmEnable
			MAX-ACCESS read-write
			STATUS current
			DESCRIPTION
				"Indicates SDI signal fail Trap Enable"
		::= { frs3000p01v1Entry 36 }

		-- 1.3.6.1.4.1.10106.3.101291.1.1.37
		frs3000p01v1SubcarrUnlock OBJECT-TYPE
			SYNTAX BitFail
			MAX-ACCESS read-only
			STATUS current
			DESCRIPTION
				"Indicates reference input subcarrier unlock fail"
		::= { frs3000p01v1Entry 37 }

		-- 1.3.6.1.4.1.10106.3.101291.1.1.38
		frs3000p01v1SubcarrUnlockTrapEnable OBJECT-TYPE
			SYNTAX AlarmEnable
			MAX-ACCESS read-write
			STATUS current
			DESCRIPTION
				"Indicates reference input subcarrier unlock fail Trap Enable"
		::= { frs3000p01v1Entry 38 }

		-- 1.3.6.1.4.1.10106.3.101291.1.1.39
		frs3000p01v1EdhError OBJECT-TYPE
			SYNTAX BitFail
			MAX-ACCESS read-only
			STATUS current
			DESCRIPTION
				"Indicates EDH status"
		::= { frs3000p01v1Entry 39 }

		-- 1.3.6.1.4.1.10106.3.101291.1.1.41
		frs3000p01v1SdiFormat OBJECT-TYPE
			SYNTAX Bit05251625
			MAX-ACCESS read-only
			STATUS current
			DESCRIPTION
				"Indicates the SDI format"
		::= { frs3000p01v1Entry 41 }

		-- 1.3.6.1.4.1.10106.3.101291.1.1.43
		frs3000p01v1RefFormat OBJECT-TYPE
			SYNTAX Bit05251625
			MAX-ACCESS read-only
			STATUS current
			DESCRIPTION
				"Indicates  the reference format"
		::= { frs3000p01v1Entry 43 }

		-- 1.3.6.1.4.1.10106.3.141701
		pds3000p01v1 OBJECT IDENTIFIER ::= { albalaProducts 141701 }

		-- 1.3.6.1.4.1.10106.3.141701.1
		pds3000p01v1Table  OBJECT-TYPE
			SYNTAX SEQUENCE OF Pds3000p01v1Entry
			MAX-ACCESS not-accessible
			STATUS current
			DESCRIPTION
				"Module  PDS3000P01V1 Table"
			::= { pds3000p01v1 1 }

		-- 1.3.6.1.4.1.10106.3.141701.1.1
		pds3000p01v1Entry  OBJECT-TYPE
			SYNTAX Pds3000p01v1Entry
			MAX-ACCESS not-accessible
			STATUS current
			DESCRIPTION
				"Module PDS3000P01V1 Entry"
			INDEX { pds3000p01v1Index }
			::= { pds3000p01v1Table 1 }

			Pds3000p01v1Entry ::=
			SEQUENCE {
				pds3000p01v1Index
				ModuleIndex,
				pds3000p01v1Lines
				Bit05251625,
				pds3000p01v1VbiMode
				Bit0Bnk1Pas,
				pds3000p01v1FailMode
				ModeFail1,
				pds3000p01v1DecoderMode
				Bit0Flt1Not,
				pds3000p01v1OperMode
				Bit0Del1Syn,
				pds3000p01v1HDelay
				DelayPixel1,
				pds3000p01v1VDelay
				DelayLines1,
				pds3000p01v1LumaGain
				GainLin1,
				pds3000p01v1ChromaGain
				GainLin1,
				pds3000p01v1BlackOffset
				BlackOffset1,
				pds3000p01v1Hue
				Sch1,
				pds3000p01v1EqualLength
				EqualLength,
				pds3000p01v1NoRef
				BitFail,
				pds3000p01v1NoRefTrapEnable
				AlarmEnable,
				pds3000p01v1RefUnlock
				BitFail,
				pds3000p01v1RefUnlockTrapEnable
				AlarmEnable,
				pds3000p01v1NoCcvs
				BitFail,
				pds3000p01v1NoCcvsTrapEnable
				AlarmEnable,
				pds3000p01v1CcvsUnlock
				BitFail,
				pds3000p01v1CcvsUnlockTrapEnable
				AlarmEnable,
				pds3000p01v1DecOvld
				BitFail,
				pds3000p01v1DecOvldTrapEnable
				AlarmEnable,
				pds3000p01v1EqualOvld
				BitFail,
				pds3000p01v1AdOvld
				BitFail,
				pds3000p01v1AdOvldTrapEnable
				AlarmEnable
			 }

		-- 1.3.6.1.4.1.10106.3.101291.1.1.1
		pds3000p01v1Index OBJECT-TYPE
			SYNTAX ModuleIndex
			MAX-ACCESS read-only
			STATUS current
			DESCRIPTION
				"Index of PDS3000P01V1 Table"
		::= { pds3000p01v1Entry 1 }

		-- 1.3.6.1.4.1.10106.3.101291.1.1.3
		pds3000p01v1Lines OBJECT-TYPE
			SYNTAX Bit05251625
			MAX-ACCESS read-write
			STATUS current
			DESCRIPTION
				"TV input signal line number"
		::= { pds3000p01v1Entry 3 }

		-- 1.3.6.1.4.1.10106.3.101291.1.1.5
		pds3000p01v1VbiMode OBJECT-TYPE
			SYNTAX Bit0Bnk1Pas
			MAX-ACCESS read-write
			STATUS current
			DESCRIPTION
				"Allows selecting if the VBI is blanked"
		::= { pds3000p01v1Entry 5 }

		-- 1.3.6.1.4.1.10106.3.101291.1.1.7
		pds3000p01v1FailMode OBJECT-TYPE
			SYNTAX ModeFail1
			MAX-ACCESS read-write
			STATUS current
			DESCRIPTION
				"Allows selecting the output video signal if the input fails"
		::= { pds3000p01v1Entry 7 }

		-- 1.3.6.1.4.1.10106.3.101291.1.1.9
		pds3000p01v1DecoderMode OBJECT-TYPE
			SYNTAX Bit0Flt1Not
			MAX-ACCESS read-write
			STATUS current
			DESCRIPTION
				"Allows selecting luminance filter"
		::= { pds3000p01v1Entry 9 }

		-- 1.3.6.1.4.1.10106.3.101291.1.1.11
		pds3000p01v1OperMode OBJECT-TYPE
			SYNTAX Bit0Del1Syn
			MAX-ACCESS read-write
			STATUS current
			DESCRIPTION
				"Allows selecting the operating mode"
		::= { pds3000p01v1Entry 11 }

		-- 1.3.6.1.4.1.10106.3.101291.1.1.13
		pds3000p01v1HDelay OBJECT-TYPE
			SYNTAX DelayPixel1
			MAX-ACCESS read-write
			STATUS current
			DESCRIPTION
				"Allows adjusting the video horizontal delay"
		::= { pds3000p01v1Entry 13 }

		-- 1.3.6.1.4.1.10106.3.101291.1.1.15
		pds3000p01v1VDelay OBJECT-TYPE
			SYNTAX DelayLines1
			MAX-ACCESS read-write
			STATUS current
			DESCRIPTION
				"Allows adjusting the video vertical delay"
		::= { pds3000p01v1Entry 15 }

		-- 1.3.6.1.4.1.10106.3.101291.1.1.17
		pds3000p01v1LumaGain OBJECT-TYPE
			SYNTAX GainLin1
			MAX-ACCESS read-write
			STATUS current
			DESCRIPTION
				"Allows adjusting the luma gain"
		::= { pds3000p01v1Entry 17 }

		-- 1.3.6.1.4.1.10106.3.101291.1.1.19
		pds3000p01v1ChromaGain OBJECT-TYPE
			SYNTAX GainLin1
			MAX-ACCESS read-write
			STATUS current
			DESCRIPTION
				"Allows adjusting the chorma gain"
		::= { pds3000p01v1Entry 19 }

		-- 1.3.6.1.4.1.10106.3.101291.1.1.21
		pds3000p01v1BlackOffset OBJECT-TYPE
			SYNTAX BlackOffset1
			MAX-ACCESS read-write
			STATUS current
			DESCRIPTION
				"Allows adjusting the black offset"
		::= { pds3000p01v1Entry 21 }

		-- 1.3.6.1.4.1.10106.3.101291.1.1.23
		pds3000p01v1Hue OBJECT-TYPE
			SYNTAX Sch1
			MAX-ACCESS read-write
			STATUS current
			DESCRIPTION
				"Allows adjusting the hue"
		::= { pds3000p01v1Entry 23 }

		-- 1.3.6.1.4.1.10106.3.101291.1.1.25
		pds3000p01v1EqualLength OBJECT-TYPE
			SYNTAX EqualLength
			MAX-ACCESS read-write
			STATUS current
			DESCRIPTION
				"Allows adjusting the cable ecualizer length"
		::= { pds3000p01v1Entry 25 }

		-- 1.3.6.1.4.1.10106.3.101291.1.1.27
		pds3000p01v1NoRef OBJECT-TYPE
			SYNTAX BitFail
			MAX-ACCESS read-only
			STATUS current
			DESCRIPTION
				"Reference input signal status"
		::= { pds3000p01v1Entry 27 }

		-- 1.3.6.1.4.1.10106.3.101291.1.1.28
		pds3000p01v1NoRefTrapEnable OBJECT-TYPE
			SYNTAX AlarmEnable
			MAX-ACCESS read-write
			STATUS current
			DESCRIPTION
				"Reference input signal status Trap Enable"
		::= { pds3000p01v1Entry 28 }

		-- 1.3.6.1.4.1.10106.3.101291.1.1.29
		pds3000p01v1RefUnlock OBJECT-TYPE
			SYNTAX BitFail
			MAX-ACCESS read-only
			STATUS current
			DESCRIPTION
				"Indicates reference input unlock fail"
		::= { pds3000p01v1Entry 29 }

		-- 1.3.6.1.4.1.10106.3.101291.1.1.30
		pds3000p01v1RefUnlockTrapEnable OBJECT-TYPE
			SYNTAX AlarmEnable
			MAX-ACCESS read-write
			STATUS current
			DESCRIPTION
				"Indicates reference input unlock fail Trap Enable"
		::= { pds3000p01v1Entry 30 }

		-- 1.3.6.1.4.1.10106.3.101291.1.1.31
		pds3000p01v1NoCcvs OBJECT-TYPE
			SYNTAX BitFail
			MAX-ACCESS read-only
			STATUS current
			DESCRIPTION
				"Composite video signal status"
		::= { pds3000p01v1Entry 31 }

		-- 1.3.6.1.4.1.10106.3.101291.1.1.32
		pds3000p01v1NoCcvsTrapEnable OBJECT-TYPE
			SYNTAX AlarmEnable
			MAX-ACCESS read-write
			STATUS current
			DESCRIPTION
				"Composite video signal status Trap Enable"
		::= { pds3000p01v1Entry 32 }

		-- 1.3.6.1.4.1.10106.3.101291.1.1.33
		pds3000p01v1CcvsUnlock OBJECT-TYPE
			SYNTAX BitFail
			MAX-ACCESS read-only
			STATUS current
			DESCRIPTION
				"Indicates reference composite video signal unlock fail"
		::= { pds3000p01v1Entry 33 }

		-- 1.3.6.1.4.1.10106.3.101291.1.1.34
		pds3000p01v1CcvsUnlockTrapEnable OBJECT-TYPE
			SYNTAX AlarmEnable
			MAX-ACCESS read-write
			STATUS current
			DESCRIPTION
				"Indicates reference composite video signal unlock fail Trap Enable"
		::= { pds3000p01v1Entry 34 }

		-- 1.3.6.1.4.1.10106.3.101291.1.1.35
		pds3000p01v1DecOvld OBJECT-TYPE
			SYNTAX BitFail
			MAX-ACCESS read-only
			STATUS current
			DESCRIPTION
				"Indicates overload in the composite video decoder"
		::= { pds3000p01v1Entry 35 }

		-- 1.3.6.1.4.1.10106.3.101291.1.1.36
		pds3000p01v1DecOvldTrapEnable OBJECT-TYPE
			SYNTAX AlarmEnable
			MAX-ACCESS read-write
			STATUS current
			DESCRIPTION
				"Indicates overload in the composite video decoder Trap Enable"
		::= { pds3000p01v1Entry 36 }

		-- 1.3.6.1.4.1.10106.3.101291.1.1.37
		pds3000p01v1EqualOvld OBJECT-TYPE
			SYNTAX BitFail
			MAX-ACCESS read-only
			STATUS current
			DESCRIPTION
				"Indicates overload in the equalizer"
		::= { pds3000p01v1Entry 37 }

		-- 1.3.6.1.4.1.10106.3.101291.1.1.39
		pds3000p01v1AdOvld OBJECT-TYPE
			SYNTAX BitFail
			MAX-ACCESS read-only
			STATUS current
			DESCRIPTION
				"Indicates overload in the A/D converter"
		::= { pds3000p01v1Entry 39 }

		-- 1.3.6.1.4.1.10106.3.101291.1.1.40
		pds3000p01v1AdOvldTrapEnable OBJECT-TYPE
			SYNTAX AlarmEnable
			MAX-ACCESS read-write
			STATUS current
			DESCRIPTION
				"Indicates overload in the A/D converter Trap Enable"
		::= { pds3000p01v1Entry 40 }

		-- 1.3.6.1.4.1.10106.3.143301
		avp1222p01v1 OBJECT IDENTIFIER ::= { albalaProducts 143301 }

		-- 1.3.6.1.4.1.10106.3.143301.1
		avp1222p01v1Table  OBJECT-TYPE
			SYNTAX SEQUENCE OF Avp1222p01v1Entry
			MAX-ACCESS not-accessible
			STATUS current
			DESCRIPTION
				"Module  AVP1222P01V1 Table"
			::= { avp1222p01v1 1 }

		-- 1.3.6.1.4.1.10106.3.143301.1.1
		avp1222p01v1Entry  OBJECT-TYPE
			SYNTAX Avp1222p01v1Entry
			MAX-ACCESS not-accessible
			STATUS current
			DESCRIPTION
				"Module AVP1222P01V1 Entry"
			INDEX { avp1222p01v1Index }
			::= { avp1222p01v1Table 1 }

			Avp1222p01v1Entry ::=
			SEQUENCE {
				avp1222p01v1Index
				ModuleIndex,
				avp1222p01v1Output1
				Inputs012,
				avp1222p01v1Output2
				Inputs012,
				avp1222p01v1SwitchMode
				PreselSwMode1,
				avp1222p01v1SwitchTime
				PreselSwTime1,
				avp1222p01v1NoSync
				BitFail,
				avp1222p01v1SyncLines
				Bit06251525,
				avp1222p01v1SyncType
				Bit0Fld1Fra
			 }

		-- 1.3.6.1.4.1.10106.3.101291.1.1.1
		avp1222p01v1Index OBJECT-TYPE
			SYNTAX ModuleIndex
			MAX-ACCESS read-only
			STATUS current
			DESCRIPTION
				"Index of AVP1222P01V1 Table"
		::= { avp1222p01v1Entry 1 }

		-- 1.3.6.1.4.1.10106.3.101291.1.1.3
		avp1222p01v1Output1 OBJECT-TYPE
			SYNTAX Inputs012
			MAX-ACCESS read-write
			STATUS current
			DESCRIPTION
				"Input routed to output 1"
		::= { avp1222p01v1Entry 3 }

		-- 1.3.6.1.4.1.10106.3.101291.1.1.5
		avp1222p01v1Output2 OBJECT-TYPE
			SYNTAX Inputs012
			MAX-ACCESS read-write
			STATUS current
			DESCRIPTION
				"Input routed to output 2"
		::= { avp1222p01v1Entry 5 }

		-- 1.3.6.1.4.1.10106.3.101291.1.1.7
		avp1222p01v1SwitchMode OBJECT-TYPE
			SYNTAX PreselSwMode1
			MAX-ACCESS read-write
			STATUS current
			DESCRIPTION
				"Allows selection switching mode: master or follow another module"
		::= { avp1222p01v1Entry 7 }

		-- 1.3.6.1.4.1.10106.3.101291.1.1.9
		avp1222p01v1SwitchTime OBJECT-TYPE
			SYNTAX PreselSwTime1
			MAX-ACCESS read-write
			STATUS current
			DESCRIPTION
				"Allows selection of switching time"
		::= { avp1222p01v1Entry 9 }

		-- 1.3.6.1.4.1.10106.3.101291.1.1.11
		avp1222p01v1NoSync OBJECT-TYPE
			SYNTAX BitFail
			MAX-ACCESS read-only
			STATUS current
			DESCRIPTION
				"Sync presence status"
		::= { avp1222p01v1Entry 11 }

		-- 1.3.6.1.4.1.10106.3.101291.1.1.13
		avp1222p01v1SyncLines OBJECT-TYPE
			SYNTAX Bit06251525
			MAX-ACCESS read-only
			STATUS current
			DESCRIPTION
				"Number of lines of sync signal"
		::= { avp1222p01v1Entry 13 }

		-- 1.3.6.1.4.1.10106.3.101291.1.1.15
		avp1222p01v1SyncType OBJECT-TYPE
			SYNTAX Bit0Fld1Fra
			MAX-ACCESS read-only
			STATUS current
			DESCRIPTION
				"Type of sync signal"
		::= { avp1222p01v1Entry 15 }

		-- 1.3.6.1.4.1.10106.3.145201
		aap0622p01v1 OBJECT IDENTIFIER ::= { albalaProducts 145201 }

		-- 1.3.6.1.4.1.10106.3.145201.1
		aap0622p01v1Table  OBJECT-TYPE
			SYNTAX SEQUENCE OF Aap0622p01v1Entry
			MAX-ACCESS not-accessible
			STATUS current
			DESCRIPTION
				"Module  AAP0622P01V1 Table"
			::= { aap0622p01v1 1 }

		-- 1.3.6.1.4.1.10106.3.145201.1.1
		aap0622p01v1Entry  OBJECT-TYPE
			SYNTAX Aap0622p01v1Entry
			MAX-ACCESS not-accessible
			STATUS current
			DESCRIPTION
				"Module AAP0622P01V1 Entry"
			INDEX { aap0622p01v1Index }
			::= { aap0622p01v1Table 1 }

			Aap0622p01v1Entry ::=
			SEQUENCE {
				aap0622p01v1Index
				ModuleIndex,
				aap0622p01v1Output1
				Inputs06,
				aap0622p01v1Output2
				Inputs06,
				aap0622p01v1SwitchMode
				PreselSwMode1
			 }

		-- 1.3.6.1.4.1.10106.3.101291.1.1.1
		aap0622p01v1Index OBJECT-TYPE
			SYNTAX ModuleIndex
			MAX-ACCESS read-only
			STATUS current
			DESCRIPTION
				"Index of AAP0622P01V1 Table"
		::= { aap0622p01v1Entry 1 }

		-- 1.3.6.1.4.1.10106.3.101291.1.1.3
		aap0622p01v1Output1 OBJECT-TYPE
			SYNTAX Inputs06
			MAX-ACCESS read-write
			STATUS current
			DESCRIPTION
				"Input routed to output 1"
		::= { aap0622p01v1Entry 3 }

		-- 1.3.6.1.4.1.10106.3.101291.1.1.5
		aap0622p01v1Output2 OBJECT-TYPE
			SYNTAX Inputs06
			MAX-ACCESS read-write
			STATUS current
			DESCRIPTION
				"Input routed to output 2"
		::= { aap0622p01v1Entry 5 }

		-- 1.3.6.1.4.1.10106.3.101291.1.1.7
		aap0622p01v1SwitchMode OBJECT-TYPE
			SYNTAX PreselSwMode1
			MAX-ACCESS read-write
			STATUS current
			DESCRIPTION
				"Allows selection switching mode: master or follow another module"
		::= { aap0622p01v1Entry 7 }

		-- 1.3.6.1.4.1.10106.3.145601
		avp0622p01v1 OBJECT IDENTIFIER ::= { albalaProducts 145601 }

		-- 1.3.6.1.4.1.10106.3.145601.1
		avp0622p01v1Table  OBJECT-TYPE
			SYNTAX SEQUENCE OF Avp0622p01v1Entry
			MAX-ACCESS not-accessible
			STATUS current
			DESCRIPTION
				"Module  AVP0622P01V1 Table"
			::= { avp0622p01v1 1 }

		-- 1.3.6.1.4.1.10106.3.145601.1.1
		avp0622p01v1Entry  OBJECT-TYPE
			SYNTAX Avp0622p01v1Entry
			MAX-ACCESS not-accessible
			STATUS current
			DESCRIPTION
				"Module AVP0622P01V1 Entry"
			INDEX { avp0622p01v1Index }
			::= { avp0622p01v1Table 1 }

			Avp0622p01v1Entry ::=
			SEQUENCE {
				avp0622p01v1Index
				ModuleIndex,
				avp0622p01v1Output1
				Inputs06,
				avp0622p01v1Output2
				Inputs06,
				avp0622p01v1SwitchMode
				PreselSwMode1,
				avp0622p01v1SwitchTime
				PreselSwTime1,
				avp0622p01v1NoSync
				BitFail,
				avp0622p01v1SyncLines
				Bit06251525,
				avp0622p01v1SyncType
				Bit0Fld1Fra
			 }

		-- 1.3.6.1.4.1.10106.3.101291.1.1.1
		avp0622p01v1Index OBJECT-TYPE
			SYNTAX ModuleIndex
			MAX-ACCESS read-only
			STATUS current
			DESCRIPTION
				"Index of AVP0622P01V1 Table"
		::= { avp0622p01v1Entry 1 }

		-- 1.3.6.1.4.1.10106.3.101291.1.1.3
		avp0622p01v1Output1 OBJECT-TYPE
			SYNTAX Inputs06
			MAX-ACCESS read-write
			STATUS current
			DESCRIPTION
				"Input routed to output 1"
		::= { avp0622p01v1Entry 3 }

		-- 1.3.6.1.4.1.10106.3.101291.1.1.5
		avp0622p01v1Output2 OBJECT-TYPE
			SYNTAX Inputs06
			MAX-ACCESS read-write
			STATUS current
			DESCRIPTION
				"Input routed to output 2"
		::= { avp0622p01v1Entry 5 }

		-- 1.3.6.1.4.1.10106.3.101291.1.1.7
		avp0622p01v1SwitchMode OBJECT-TYPE
			SYNTAX PreselSwMode1
			MAX-ACCESS read-write
			STATUS current
			DESCRIPTION
				"Allows selection switching mode: master or follow another module"
		::= { avp0622p01v1Entry 7 }

		-- 1.3.6.1.4.1.10106.3.101291.1.1.9
		avp0622p01v1SwitchTime OBJECT-TYPE
			SYNTAX PreselSwTime1
			MAX-ACCESS read-write
			STATUS current
			DESCRIPTION
				"Allows selection of switching time"
		::= { avp0622p01v1Entry 9 }

		-- 1.3.6.1.4.1.10106.3.101291.1.1.11
		avp0622p01v1NoSync OBJECT-TYPE
			SYNTAX BitFail
			MAX-ACCESS read-only
			STATUS current
			DESCRIPTION
				"Sync presence status"
		::= { avp0622p01v1Entry 11 }

		-- 1.3.6.1.4.1.10106.3.101291.1.1.13
		avp0622p01v1SyncLines OBJECT-TYPE
			SYNTAX Bit06251525
			MAX-ACCESS read-only
			STATUS current
			DESCRIPTION
				"Number of lines of sync signal"
		::= { avp0622p01v1Entry 13 }

		-- 1.3.6.1.4.1.10106.3.101291.1.1.15
		avp0622p01v1SyncType OBJECT-TYPE
			SYNTAX Bit0Fld1Fra
			MAX-ACCESS read-only
			STATUS current
			DESCRIPTION
				"Type of sync signal"
		::= { avp0622p01v1Entry 15 }

		-- 1.3.6.1.4.1.10106.3.147801
		aad3024p01v1 OBJECT IDENTIFIER ::= { albalaProducts 147801 }

		-- 1.3.6.1.4.1.10106.3.147801.1
		aad3024p01v1Table  OBJECT-TYPE
			SYNTAX SEQUENCE OF Aad3024p01v1Entry
			MAX-ACCESS not-accessible
			STATUS current
			DESCRIPTION
				"Module  AAD3024P01V1 Table"
			::= { aad3024p01v1 1 }

		-- 1.3.6.1.4.1.10106.3.147801.1.1
		aad3024p01v1Entry  OBJECT-TYPE
			SYNTAX Aad3024p01v1Entry
			MAX-ACCESS not-accessible
			STATUS current
			DESCRIPTION
				"Module AAD3024P01V1 Entry"
			INDEX { aad3024p01v1Index }
			::= { aad3024p01v1Table 1 }

			Aad3024p01v1Entry ::=
			SEQUENCE {
				aad3024p01v1Index
				ModuleIndex,
				aad3024p01v1GainRA
				GainDb1,
				aad3024p01v1GainLA
				GainDb1,
				aad3024p01v1GainRB
				GainDb1,
				aad3024p01v1GainLB
				GainDb1,
				aad3024p01v1NoSigTout
				TimeS2,
				aad3024p01v1SilThrLevel
				LevelDbuD5,
				aad3024p01v1OvlThrLevel
				LevelDbuD5,
				aad3024p01v1SilenceRA
				BitFail,
				aad3024p01v1SilenceRATrapEnable
				AlarmEnable,
				aad3024p01v1SilenceLA
				BitFail,
				aad3024p01v1SilenceLATrapEnable
				AlarmEnable,
				aad3024p01v1AntiphaseA
				BitFail,
				aad3024p01v1AntiphaseATrapEnable
				AlarmEnable,
				aad3024p01v1OverloadRA
				BitFail,
				aad3024p01v1OverloadRATrapEnable
				AlarmEnable,
				aad3024p01v1OverloadLA
				BitFail,
				aad3024p01v1OverloadLATrapEnable
				AlarmEnable,
				aad3024p01v1SilenceRB
				BitFail,
				aad3024p01v1SilenceRBTrapEnable
				AlarmEnable,
				aad3024p01v1SilenceLB
				BitFail,
				aad3024p01v1SilenceLBTrapEnable
				AlarmEnable,
				aad3024p01v1AntiphaseB
				BitFail,
				aad3024p01v1AntiphaseBTrapEnable
				AlarmEnable,
				aad3024p01v1OverloadRB
				BitFail,
				aad3024p01v1OverloadRBTrapEnable
				AlarmEnable,
				aad3024p01v1OverloadLB
				BitFail,
				aad3024p01v1OverloadLBTrapEnable
				AlarmEnable,
				aad3024p01v1LevelRA
				LevelDbuD5,
				aad3024p01v1LevelLA
				LevelDbuD5,
				aad3024p01v1LevelRB
				LevelDbuD5,
				aad3024p01v1LevelLB
				LevelDbuD5
			 }

		-- 1.3.6.1.4.1.10106.3.101291.1.1.1
		aad3024p01v1Index OBJECT-TYPE
			SYNTAX ModuleIndex
			MAX-ACCESS read-only
			STATUS current
			DESCRIPTION
				"Index of AAD3024P01V1 Table"
		::= { aad3024p01v1Entry 1 }

		-- 1.3.6.1.4.1.10106.3.101291.1.1.3
		aad3024p01v1GainRA OBJECT-TYPE
			SYNTAX GainDb1
			MAX-ACCESS read-write
			STATUS current
			DESCRIPTION
				"Gain right channel"
		::= { aad3024p01v1Entry 3 }

		-- 1.3.6.1.4.1.10106.3.101291.1.1.5
		aad3024p01v1GainLA OBJECT-TYPE
			SYNTAX GainDb1
			MAX-ACCESS read-write
			STATUS current
			DESCRIPTION
				"Gain left channel"
		::= { aad3024p01v1Entry 5 }

		-- 1.3.6.1.4.1.10106.3.101291.1.1.7
		aad3024p01v1GainRB OBJECT-TYPE
			SYNTAX GainDb1
			MAX-ACCESS read-write
			STATUS current
			DESCRIPTION
				"Gain right channel"
		::= { aad3024p01v1Entry 7 }

		-- 1.3.6.1.4.1.10106.3.101291.1.1.9
		aad3024p01v1GainLB OBJECT-TYPE
			SYNTAX GainDb1
			MAX-ACCESS read-write
			STATUS current
			DESCRIPTION
				"Gain left channel"
		::= { aad3024p01v1Entry 9 }

		-- 1.3.6.1.4.1.10106.3.101291.1.1.11
		aad3024p01v1NoSigTout OBJECT-TYPE
			SYNTAX TimeS2
			MAX-ACCESS read-write
			STATUS current
			DESCRIPTION
				"Silence timeout"
		::= { aad3024p01v1Entry 11 }

		-- 1.3.6.1.4.1.10106.3.101291.1.1.13
		aad3024p01v1SilThrLevel OBJECT-TYPE
			SYNTAX LevelDbuD5
			MAX-ACCESS read-write
			STATUS current
			DESCRIPTION
				"Silence threshold level"
		::= { aad3024p01v1Entry 13 }

		-- 1.3.6.1.4.1.10106.3.101291.1.1.15
		aad3024p01v1OvlThrLevel OBJECT-TYPE
			SYNTAX LevelDbuD5
			MAX-ACCESS read-write
			STATUS current
			DESCRIPTION
				"Overload threshold level"
		::= { aad3024p01v1Entry 15 }

		-- 1.3.6.1.4.1.10106.3.101291.1.1.17
		aad3024p01v1SilenceRA OBJECT-TYPE
			SYNTAX BitFail
			MAX-ACCESS read-only
			STATUS current
			DESCRIPTION
				"Right channel silence fail"
		::= { aad3024p01v1Entry 17 }

		-- 1.3.6.1.4.1.10106.3.101291.1.1.18
		aad3024p01v1SilenceRATrapEnable OBJECT-TYPE
			SYNTAX AlarmEnable
			MAX-ACCESS read-write
			STATUS current
			DESCRIPTION
				"Right channel silence fail Trap Enable"
		::= { aad3024p01v1Entry 18 }

		-- 1.3.6.1.4.1.10106.3.101291.1.1.19
		aad3024p01v1SilenceLA OBJECT-TYPE
			SYNTAX BitFail
			MAX-ACCESS read-only
			STATUS current
			DESCRIPTION
				"Left channel silence fail"
		::= { aad3024p01v1Entry 19 }

		-- 1.3.6.1.4.1.10106.3.101291.1.1.20
		aad3024p01v1SilenceLATrapEnable OBJECT-TYPE
			SYNTAX AlarmEnable
			MAX-ACCESS read-write
			STATUS current
			DESCRIPTION
				"Left channel silence fail Trap Enable"
		::= { aad3024p01v1Entry 20 }

		-- 1.3.6.1.4.1.10106.3.101291.1.1.21
		aad3024p01v1AntiphaseA OBJECT-TYPE
			SYNTAX BitFail
			MAX-ACCESS read-only
			STATUS current
			DESCRIPTION
				"Antiphase fail"
		::= { aad3024p01v1Entry 21 }

		-- 1.3.6.1.4.1.10106.3.101291.1.1.22
		aad3024p01v1AntiphaseATrapEnable OBJECT-TYPE
			SYNTAX AlarmEnable
			MAX-ACCESS read-write
			STATUS current
			DESCRIPTION
				"Antiphase fail Trap Enable"
		::= { aad3024p01v1Entry 22 }

		-- 1.3.6.1.4.1.10106.3.101291.1.1.23
		aad3024p01v1OverloadRA OBJECT-TYPE
			SYNTAX BitFail
			MAX-ACCESS read-only
			STATUS current
			DESCRIPTION
				"Right channel overload fail"
		::= { aad3024p01v1Entry 23 }

		-- 1.3.6.1.4.1.10106.3.101291.1.1.24
		aad3024p01v1OverloadRATrapEnable OBJECT-TYPE
			SYNTAX AlarmEnable
			MAX-ACCESS read-write
			STATUS current
			DESCRIPTION
				"Right channel overload fail Trap Enable"
		::= { aad3024p01v1Entry 24 }

		-- 1.3.6.1.4.1.10106.3.101291.1.1.25
		aad3024p01v1OverloadLA OBJECT-TYPE
			SYNTAX BitFail
			MAX-ACCESS read-only
			STATUS current
			DESCRIPTION
				"Left channel overload fail"
		::= { aad3024p01v1Entry 25 }

		-- 1.3.6.1.4.1.10106.3.101291.1.1.26
		aad3024p01v1OverloadLATrapEnable OBJECT-TYPE
			SYNTAX AlarmEnable
			MAX-ACCESS read-write
			STATUS current
			DESCRIPTION
				"Left channel overload fail Trap Enable"
		::= { aad3024p01v1Entry 26 }

		-- 1.3.6.1.4.1.10106.3.101291.1.1.27
		aad3024p01v1SilenceRB OBJECT-TYPE
			SYNTAX BitFail
			MAX-ACCESS read-only
			STATUS current
			DESCRIPTION
				"Right channel silence fail"
		::= { aad3024p01v1Entry 27 }

		-- 1.3.6.1.4.1.10106.3.101291.1.1.28
		aad3024p01v1SilenceRBTrapEnable OBJECT-TYPE
			SYNTAX AlarmEnable
			MAX-ACCESS read-write
			STATUS current
			DESCRIPTION
				"Right channel silence fail Trap Enable"
		::= { aad3024p01v1Entry 28 }

		-- 1.3.6.1.4.1.10106.3.101291.1.1.29
		aad3024p01v1SilenceLB OBJECT-TYPE
			SYNTAX BitFail
			MAX-ACCESS read-only
			STATUS current
			DESCRIPTION
				"Left channel silence fail"
		::= { aad3024p01v1Entry 29 }

		-- 1.3.6.1.4.1.10106.3.101291.1.1.30
		aad3024p01v1SilenceLBTrapEnable OBJECT-TYPE
			SYNTAX AlarmEnable
			MAX-ACCESS read-write
			STATUS current
			DESCRIPTION
				"Left channel silence fail Trap Enable"
		::= { aad3024p01v1Entry 30 }

		-- 1.3.6.1.4.1.10106.3.101291.1.1.31
		aad3024p01v1AntiphaseB OBJECT-TYPE
			SYNTAX BitFail
			MAX-ACCESS read-only
			STATUS current
			DESCRIPTION
				"Antiphase fail"
		::= { aad3024p01v1Entry 31 }

		-- 1.3.6.1.4.1.10106.3.101291.1.1.32
		aad3024p01v1AntiphaseBTrapEnable OBJECT-TYPE
			SYNTAX AlarmEnable
			MAX-ACCESS read-write
			STATUS current
			DESCRIPTION
				"Antiphase fail Trap Enable"
		::= { aad3024p01v1Entry 32 }

		-- 1.3.6.1.4.1.10106.3.101291.1.1.33
		aad3024p01v1OverloadRB OBJECT-TYPE
			SYNTAX BitFail
			MAX-ACCESS read-only
			STATUS current
			DESCRIPTION
				"Right channel overload fail"
		::= { aad3024p01v1Entry 33 }

		-- 1.3.6.1.4.1.10106.3.101291.1.1.34
		aad3024p01v1OverloadRBTrapEnable OBJECT-TYPE
			SYNTAX AlarmEnable
			MAX-ACCESS read-write
			STATUS current
			DESCRIPTION
				"Right channel overload fail Trap Enable"
		::= { aad3024p01v1Entry 34 }

		-- 1.3.6.1.4.1.10106.3.101291.1.1.35
		aad3024p01v1OverloadLB OBJECT-TYPE
			SYNTAX BitFail
			MAX-ACCESS read-only
			STATUS current
			DESCRIPTION
				"Left channel overload fail"
		::= { aad3024p01v1Entry 35 }

		-- 1.3.6.1.4.1.10106.3.101291.1.1.36
		aad3024p01v1OverloadLBTrapEnable OBJECT-TYPE
			SYNTAX AlarmEnable
			MAX-ACCESS read-write
			STATUS current
			DESCRIPTION
				"Left channel overload fail Trap Enable"
		::= { aad3024p01v1Entry 36 }

		-- 1.3.6.1.4.1.10106.3.101291.1.1.37
		aad3024p01v1LevelRA OBJECT-TYPE
			SYNTAX LevelDbuD5
			MAX-ACCESS read-only
			STATUS current
			DESCRIPTION
				"Right channel level"
		::= { aad3024p01v1Entry 37 }

		-- 1.3.6.1.4.1.10106.3.101291.1.1.39
		aad3024p01v1LevelLA OBJECT-TYPE
			SYNTAX LevelDbuD5
			MAX-ACCESS read-only
			STATUS current
			DESCRIPTION
				"Left channel level"
		::= { aad3024p01v1Entry 39 }

		-- 1.3.6.1.4.1.10106.3.101291.1.1.41
		aad3024p01v1LevelRB OBJECT-TYPE
			SYNTAX LevelDbuD5
			MAX-ACCESS read-only
			STATUS current
			DESCRIPTION
				"Right channel level"
		::= { aad3024p01v1Entry 41 }

		-- 1.3.6.1.4.1.10106.3.101291.1.1.43
		aad3024p01v1LevelLB OBJECT-TYPE
			SYNTAX LevelDbuD5
			MAX-ACCESS read-only
			STATUS current
			DESCRIPTION
				"Left channel level"
		::= { aad3024p01v1Entry 43 }

		-- 1.3.6.1.4.1.10106.3.147901
		aad3014p01v1 OBJECT IDENTIFIER ::= { albalaProducts 147901 }

		-- 1.3.6.1.4.1.10106.3.147901.1
		aad3014p01v1Table  OBJECT-TYPE
			SYNTAX SEQUENCE OF Aad3014p01v1Entry
			MAX-ACCESS not-accessible
			STATUS current
			DESCRIPTION
				"Module  AAD3014P01V1 Table"
			::= { aad3014p01v1 1 }

		-- 1.3.6.1.4.1.10106.3.147901.1.1
		aad3014p01v1Entry  OBJECT-TYPE
			SYNTAX Aad3014p01v1Entry
			MAX-ACCESS not-accessible
			STATUS current
			DESCRIPTION
				"Module AAD3014P01V1 Entry"
			INDEX { aad3014p01v1Index }
			::= { aad3014p01v1Table 1 }

			Aad3014p01v1Entry ::=
			SEQUENCE {
				aad3014p01v1Index
				ModuleIndex,
				aad3014p01v1GainR
				GainDb1,
				aad3014p01v1GainL
				GainDb1,
				aad3014p01v1NoSigTout
				TimeS2,
				aad3014p01v1SilThrLevel
				LevelDbuD5,
				aad3014p01v1OvlThrLevel
				LevelDbuD5,
				aad3014p01v1SilenceR
				BitFail,
				aad3014p01v1SilenceRTrapEnable
				AlarmEnable,
				aad3014p01v1SilenceL
				BitFail,
				aad3014p01v1SilenceLTrapEnable
				AlarmEnable,
				aad3014p01v1Antiphase
				BitFail,
				aad3014p01v1AntiphaseTrapEnable
				AlarmEnable,
				aad3014p01v1OverloadR
				BitFail,
				aad3014p01v1OverloadRTrapEnable
				AlarmEnable,
				aad3014p01v1OverloadL
				BitFail,
				aad3014p01v1OverloadLTrapEnable
				AlarmEnable,
				aad3014p01v1OverloadRl
				BitFail,
				aad3014p01v1OverloadRlTrapEnable
				AlarmEnable,
				aad3014p01v1LevelR
				LevelDbuD5,
				aad3014p01v1LevelL
				LevelDbuD5
			 }

		-- 1.3.6.1.4.1.10106.3.101291.1.1.1
		aad3014p01v1Index OBJECT-TYPE
			SYNTAX ModuleIndex
			MAX-ACCESS read-only
			STATUS current
			DESCRIPTION
				"Index of AAD3014P01V1 Table"
		::= { aad3014p01v1Entry 1 }

		-- 1.3.6.1.4.1.10106.3.101291.1.1.3
		aad3014p01v1GainR OBJECT-TYPE
			SYNTAX GainDb1
			MAX-ACCESS read-write
			STATUS current
			DESCRIPTION
				"Gain right channel"
		::= { aad3014p01v1Entry 3 }

		-- 1.3.6.1.4.1.10106.3.101291.1.1.5
		aad3014p01v1GainL OBJECT-TYPE
			SYNTAX GainDb1
			MAX-ACCESS read-write
			STATUS current
			DESCRIPTION
				"Gain left channel"
		::= { aad3014p01v1Entry 5 }

		-- 1.3.6.1.4.1.10106.3.101291.1.1.7
		aad3014p01v1NoSigTout OBJECT-TYPE
			SYNTAX TimeS2
			MAX-ACCESS read-write
			STATUS current
			DESCRIPTION
				"Silence timeout"
		::= { aad3014p01v1Entry 7 }

		-- 1.3.6.1.4.1.10106.3.101291.1.1.9
		aad3014p01v1SilThrLevel OBJECT-TYPE
			SYNTAX LevelDbuD5
			MAX-ACCESS read-write
			STATUS current
			DESCRIPTION
				"Silence threshold level"
		::= { aad3014p01v1Entry 9 }

		-- 1.3.6.1.4.1.10106.3.101291.1.1.11
		aad3014p01v1OvlThrLevel OBJECT-TYPE
			SYNTAX LevelDbuD5
			MAX-ACCESS read-write
			STATUS current
			DESCRIPTION
				"Overload threshold level"
		::= { aad3014p01v1Entry 11 }

		-- 1.3.6.1.4.1.10106.3.101291.1.1.13
		aad3014p01v1SilenceR OBJECT-TYPE
			SYNTAX BitFail
			MAX-ACCESS read-only
			STATUS current
			DESCRIPTION
				"Right channel silence fail"
		::= { aad3014p01v1Entry 13 }

		-- 1.3.6.1.4.1.10106.3.101291.1.1.14
		aad3014p01v1SilenceRTrapEnable OBJECT-TYPE
			SYNTAX AlarmEnable
			MAX-ACCESS read-write
			STATUS current
			DESCRIPTION
				"Right channel silence fail Trap Enable"
		::= { aad3014p01v1Entry 14 }

		-- 1.3.6.1.4.1.10106.3.101291.1.1.15
		aad3014p01v1SilenceL OBJECT-TYPE
			SYNTAX BitFail
			MAX-ACCESS read-only
			STATUS current
			DESCRIPTION
				"Left channel silence fail"
		::= { aad3014p01v1Entry 15 }

		-- 1.3.6.1.4.1.10106.3.101291.1.1.16
		aad3014p01v1SilenceLTrapEnable OBJECT-TYPE
			SYNTAX AlarmEnable
			MAX-ACCESS read-write
			STATUS current
			DESCRIPTION
				"Left channel silence fail Trap Enable"
		::= { aad3014p01v1Entry 16 }

		-- 1.3.6.1.4.1.10106.3.101291.1.1.17
		aad3014p01v1Antiphase OBJECT-TYPE
			SYNTAX BitFail
			MAX-ACCESS read-only
			STATUS current
			DESCRIPTION
				"Antiphase fail"
		::= { aad3014p01v1Entry 17 }

		-- 1.3.6.1.4.1.10106.3.101291.1.1.18
		aad3014p01v1AntiphaseTrapEnable OBJECT-TYPE
			SYNTAX AlarmEnable
			MAX-ACCESS read-write
			STATUS current
			DESCRIPTION
				"Antiphase fail Trap Enable"
		::= { aad3014p01v1Entry 18 }

		-- 1.3.6.1.4.1.10106.3.101291.1.1.19
		aad3014p01v1OverloadR OBJECT-TYPE
			SYNTAX BitFail
			MAX-ACCESS read-only
			STATUS current
			DESCRIPTION
				"Right channel overload fail"
		::= { aad3014p01v1Entry 19 }

		-- 1.3.6.1.4.1.10106.3.101291.1.1.20
		aad3014p01v1OverloadRTrapEnable OBJECT-TYPE
			SYNTAX AlarmEnable
			MAX-ACCESS read-write
			STATUS current
			DESCRIPTION
				"Right channel overload fail Trap Enable"
		::= { aad3014p01v1Entry 20 }

		-- 1.3.6.1.4.1.10106.3.101291.1.1.21
		aad3014p01v1OverloadL OBJECT-TYPE
			SYNTAX BitFail
			MAX-ACCESS read-only
			STATUS current
			DESCRIPTION
				"Left channel overload fail"
		::= { aad3014p01v1Entry 21 }

		-- 1.3.6.1.4.1.10106.3.101291.1.1.22
		aad3014p01v1OverloadLTrapEnable OBJECT-TYPE
			SYNTAX AlarmEnable
			MAX-ACCESS read-write
			STATUS current
			DESCRIPTION
				"Left channel overload fail Trap Enable"
		::= { aad3014p01v1Entry 22 }

		-- 1.3.6.1.4.1.10106.3.101291.1.1.23
		aad3014p01v1OverloadRl OBJECT-TYPE
			SYNTAX BitFail
			MAX-ACCESS read-only
			STATUS current
			DESCRIPTION
				"Right+left channel overload fail"
		::= { aad3014p01v1Entry 23 }

		-- 1.3.6.1.4.1.10106.3.101291.1.1.24
		aad3014p01v1OverloadRlTrapEnable OBJECT-TYPE
			SYNTAX AlarmEnable
			MAX-ACCESS read-write
			STATUS current
			DESCRIPTION
				"Right+left channel overload fail Trap Enable"
		::= { aad3014p01v1Entry 24 }

		-- 1.3.6.1.4.1.10106.3.101291.1.1.25
		aad3014p01v1LevelR OBJECT-TYPE
			SYNTAX LevelDbuD5
			MAX-ACCESS read-only
			STATUS current
			DESCRIPTION
				"Right channel level"
		::= { aad3014p01v1Entry 25 }

		-- 1.3.6.1.4.1.10106.3.101291.1.1.27
		aad3014p01v1LevelL OBJECT-TYPE
			SYNTAX LevelDbuD5
			MAX-ACCESS read-only
			STATUS current
			DESCRIPTION
				"Left channel level"
		::= { aad3014p01v1Entry 27 }

		-- 1.3.6.1.4.1.10106.3.147902
		aad3014c01v2 OBJECT IDENTIFIER ::= { albalaProducts 147902 }

		-- 1.3.6.1.4.1.10106.3.147902.1
		aad3014c01v2Table  OBJECT-TYPE
			SYNTAX SEQUENCE OF Aad3014c01v2Entry
			MAX-ACCESS not-accessible
			STATUS current
			DESCRIPTION
				"Module  AAD3014C01V2 Table"
			::= { aad3014c01v2 1 }

		-- 1.3.6.1.4.1.10106.3.147902.1.1
		aad3014c01v2Entry  OBJECT-TYPE
			SYNTAX Aad3014c01v2Entry
			MAX-ACCESS not-accessible
			STATUS current
			DESCRIPTION
				"Module AAD3014C01V2 Entry"
			INDEX { aad3014c01v2Index }
			::= { aad3014c01v2Table 1 }

			Aad3014c01v2Entry ::=
			SEQUENCE {
				aad3014c01v2Index
				ModuleIndex,
				aad3014c01v2Mono
				Bit0Dis1Ena,
				aad3014c01v2GainR
				Gain315dbMute,
				aad3014c01v2GainL
				Gain315dbMute,
				aad3014c01v2OvlThrLevel
				LevelDbuD2,
				aad3014c01v2SilThrLevel
				LevelDbuD2,
				aad3014c01v2NoSigTout
				TimeS2,
				aad3014c01v2SilenceR
				BitFail,
				aad3014c01v2SilenceRTrapEnable
				AlarmEnable,
				aad3014c01v2SilenceL
				BitFail,
				aad3014c01v2SilenceLTrapEnable
				AlarmEnable,
				aad3014c01v2OverloadR
				BitFail,
				aad3014c01v2OverloadRTrapEnable
				AlarmEnable,
				aad3014c01v2OverloadL
				BitFail,
				aad3014c01v2OverloadLTrapEnable
				AlarmEnable,
				aad3014c01v2PkLevelR
				LevelDbuD2,
				aad3014c01v2PkLevelL
				LevelDbuD2,
				aad3014c01v2SerialNo
				SerialNo
			 }

		-- 1.3.6.1.4.1.10106.3.101291.1.1.1
		aad3014c01v2Index OBJECT-TYPE
			SYNTAX ModuleIndex
			MAX-ACCESS read-only
			STATUS current
			DESCRIPTION
				"Index of AAD3014C01V2 Table"
		::= { aad3014c01v2Entry 1 }

		-- 1.3.6.1.4.1.10106.3.101291.1.1.3
		aad3014c01v2Mono OBJECT-TYPE
			SYNTAX Bit0Dis1Ena
			MAX-ACCESS read-write
			STATUS current
			DESCRIPTION
				"Allows summing R&L to make a monophonic channel"
		::= { aad3014c01v2Entry 3 }

		-- 1.3.6.1.4.1.10106.3.101291.1.1.5
		aad3014c01v2GainR OBJECT-TYPE
			SYNTAX Gain315dbMute
			MAX-ACCESS read-write
			STATUS current
			DESCRIPTION
				"Allows adjusting right channel gain"
		::= { aad3014c01v2Entry 5 }

		-- 1.3.6.1.4.1.10106.3.101291.1.1.7
		aad3014c01v2GainL OBJECT-TYPE
			SYNTAX Gain315dbMute
			MAX-ACCESS read-write
			STATUS current
			DESCRIPTION
				"Allows adjusting left channel gain"
		::= { aad3014c01v2Entry 7 }

		-- 1.3.6.1.4.1.10106.3.101291.1.1.9
		aad3014c01v2OvlThrLevel OBJECT-TYPE
			SYNTAX LevelDbuD2
			MAX-ACCESS read-write
			STATUS current
			DESCRIPTION
				"Overload threshold level"
		::= { aad3014c01v2Entry 9 }

		-- 1.3.6.1.4.1.10106.3.101291.1.1.11
		aad3014c01v2SilThrLevel OBJECT-TYPE
			SYNTAX LevelDbuD2
			MAX-ACCESS read-write
			STATUS current
			DESCRIPTION
				"Silence threshold level"
		::= { aad3014c01v2Entry 11 }

		-- 1.3.6.1.4.1.10106.3.101291.1.1.13
		aad3014c01v2NoSigTout OBJECT-TYPE
			SYNTAX TimeS2
			MAX-ACCESS read-write
			STATUS current
			DESCRIPTION
				"Silence timeout"
		::= { aad3014c01v2Entry 13 }

		-- 1.3.6.1.4.1.10106.3.101291.1.1.15
		aad3014c01v2SilenceR OBJECT-TYPE
			SYNTAX BitFail
			MAX-ACCESS read-only
			STATUS current
			DESCRIPTION
				"Silence fail right channel"
		::= { aad3014c01v2Entry 15 }

		-- 1.3.6.1.4.1.10106.3.101291.1.1.16
		aad3014c01v2SilenceRTrapEnable OBJECT-TYPE
			SYNTAX AlarmEnable
			MAX-ACCESS read-write
			STATUS current
			DESCRIPTION
				"Silence fail right channel Trap Enable"
		::= { aad3014c01v2Entry 16 }

		-- 1.3.6.1.4.1.10106.3.101291.1.1.17
		aad3014c01v2SilenceL OBJECT-TYPE
			SYNTAX BitFail
			MAX-ACCESS read-only
			STATUS current
			DESCRIPTION
				"Silence fail left channel"
		::= { aad3014c01v2Entry 17 }

		-- 1.3.6.1.4.1.10106.3.101291.1.1.18
		aad3014c01v2SilenceLTrapEnable OBJECT-TYPE
			SYNTAX AlarmEnable
			MAX-ACCESS read-write
			STATUS current
			DESCRIPTION
				"Silence fail left channel Trap Enable"
		::= { aad3014c01v2Entry 18 }

		-- 1.3.6.1.4.1.10106.3.101291.1.1.19
		aad3014c01v2OverloadR OBJECT-TYPE
			SYNTAX BitFail
			MAX-ACCESS read-only
			STATUS current
			DESCRIPTION
				"Overload fail right channel"
		::= { aad3014c01v2Entry 19 }

		-- 1.3.6.1.4.1.10106.3.101291.1.1.20
		aad3014c01v2OverloadRTrapEnable OBJECT-TYPE
			SYNTAX AlarmEnable
			MAX-ACCESS read-write
			STATUS current
			DESCRIPTION
				"Overload fail right channel Trap Enable"
		::= { aad3014c01v2Entry 20 }

		-- 1.3.6.1.4.1.10106.3.101291.1.1.21
		aad3014c01v2OverloadL OBJECT-TYPE
			SYNTAX BitFail
			MAX-ACCESS read-only
			STATUS current
			DESCRIPTION
				"Overload fail left channel"
		::= { aad3014c01v2Entry 21 }

		-- 1.3.6.1.4.1.10106.3.101291.1.1.22
		aad3014c01v2OverloadLTrapEnable OBJECT-TYPE
			SYNTAX AlarmEnable
			MAX-ACCESS read-write
			STATUS current
			DESCRIPTION
				"Overload fail left channel Trap Enable"
		::= { aad3014c01v2Entry 22 }

		-- 1.3.6.1.4.1.10106.3.101291.1.1.23
		aad3014c01v2PkLevelR OBJECT-TYPE
			SYNTAX LevelDbuD2
			MAX-ACCESS read-only
			STATUS current
			DESCRIPTION
				"Peak level right channel"
		::= { aad3014c01v2Entry 23 }

		-- 1.3.6.1.4.1.10106.3.101291.1.1.25
		aad3014c01v2PkLevelL OBJECT-TYPE
			SYNTAX LevelDbuD2
			MAX-ACCESS read-only
			STATUS current
			DESCRIPTION
				"Peak level left channel"
		::= { aad3014c01v2Entry 25 }

		-- 1.3.6.1.4.1.10106.3.101291.1.1.27
		aad3014c01v2SerialNo OBJECT-TYPE
			SYNTAX SerialNo
			MAX-ACCESS read-only
			STATUS current
			DESCRIPTION
				"Serial number"
		::= { aad3014c01v2Entry 27 }

		-- 1.3.6.1.4.1.10106.3.148001
		aap0621p01v1 OBJECT IDENTIFIER ::= { albalaProducts 148001 }

		-- 1.3.6.1.4.1.10106.3.148001.1
		aap0621p01v1Table  OBJECT-TYPE
			SYNTAX SEQUENCE OF Aap0621p01v1Entry
			MAX-ACCESS not-accessible
			STATUS current
			DESCRIPTION
				"Module  AAP0621P01V1 Table"
			::= { aap0621p01v1 1 }

		-- 1.3.6.1.4.1.10106.3.148001.1.1
		aap0621p01v1Entry  OBJECT-TYPE
			SYNTAX Aap0621p01v1Entry
			MAX-ACCESS not-accessible
			STATUS current
			DESCRIPTION
				"Module AAP0621P01V1 Entry"
			INDEX { aap0621p01v1Index }
			::= { aap0621p01v1Table 1 }

			Aap0621p01v1Entry ::=
			SEQUENCE {
				aap0621p01v1Index
				ModuleIndex,
				aap0621p01v1Output1
				Inputs06,
				aap0621p01v1SwitchMode
				PreselSwMode1
			 }

		-- 1.3.6.1.4.1.10106.3.101291.1.1.1
		aap0621p01v1Index OBJECT-TYPE
			SYNTAX ModuleIndex
			MAX-ACCESS read-only
			STATUS current
			DESCRIPTION
				"Index of AAP0621P01V1 Table"
		::= { aap0621p01v1Entry 1 }

		-- 1.3.6.1.4.1.10106.3.101291.1.1.3
		aap0621p01v1Output1 OBJECT-TYPE
			SYNTAX Inputs06
			MAX-ACCESS read-write
			STATUS current
			DESCRIPTION
				"Input routed to output 1"
		::= { aap0621p01v1Entry 3 }

		-- 1.3.6.1.4.1.10106.3.101291.1.1.5
		aap0621p01v1SwitchMode OBJECT-TYPE
			SYNTAX PreselSwMode1
			MAX-ACCESS read-write
			STATUS current
			DESCRIPTION
				"Allows selection switching mode: master or follow another module"
		::= { aap0621p01v1Entry 5 }

		-- 1.3.6.1.4.1.10106.3.148101
		aap1222p01v1 OBJECT IDENTIFIER ::= { albalaProducts 148101 }

		-- 1.3.6.1.4.1.10106.3.148101.1
		aap1222p01v1Table  OBJECT-TYPE
			SYNTAX SEQUENCE OF Aap1222p01v1Entry
			MAX-ACCESS not-accessible
			STATUS current
			DESCRIPTION
				"Module  AAP1222P01V1 Table"
			::= { aap1222p01v1 1 }

		-- 1.3.6.1.4.1.10106.3.148101.1.1
		aap1222p01v1Entry  OBJECT-TYPE
			SYNTAX Aap1222p01v1Entry
			MAX-ACCESS not-accessible
			STATUS current
			DESCRIPTION
				"Module AAP1222P01V1 Entry"
			INDEX { aap1222p01v1Index }
			::= { aap1222p01v1Table 1 }

			Aap1222p01v1Entry ::=
			SEQUENCE {
				aap1222p01v1Index
				ModuleIndex,
				aap1222p01v1Output1
				Inputs012,
				aap1222p01v1Output2
				Inputs012,
				aap1222p01v1SwitchMode
				PreselSwMode1
			 }

		-- 1.3.6.1.4.1.10106.3.101291.1.1.1
		aap1222p01v1Index OBJECT-TYPE
			SYNTAX ModuleIndex
			MAX-ACCESS read-only
			STATUS current
			DESCRIPTION
				"Index of AAP1222P01V1 Table"
		::= { aap1222p01v1Entry 1 }

		-- 1.3.6.1.4.1.10106.3.101291.1.1.3
		aap1222p01v1Output1 OBJECT-TYPE
			SYNTAX Inputs012
			MAX-ACCESS read-write
			STATUS current
			DESCRIPTION
				"Input routed to output 1"
		::= { aap1222p01v1Entry 3 }

		-- 1.3.6.1.4.1.10106.3.101291.1.1.5
		aap1222p01v1Output2 OBJECT-TYPE
			SYNTAX Inputs012
			MAX-ACCESS read-write
			STATUS current
			DESCRIPTION
				"Input routed to output 2"
		::= { aap1222p01v1Entry 5 }

		-- 1.3.6.1.4.1.10106.3.101291.1.1.7
		aap1222p01v1SwitchMode OBJECT-TYPE
			SYNTAX PreselSwMode1
			MAX-ACCESS read-write
			STATUS current
			DESCRIPTION
				"Allows selection switching mode: master or follow another module"
		::= { aap1222p01v1Entry 7 }

		-- 1.3.6.1.4.1.10106.3.149301
		sct3000c02v1 OBJECT IDENTIFIER ::= { albalaProducts 149301 }

		-- 1.3.6.1.4.1.10106.3.149301.1
		sct3000c02v1Table  OBJECT-TYPE
			SYNTAX SEQUENCE OF Sct3000c02v1Entry
			MAX-ACCESS not-accessible
			STATUS current
			DESCRIPTION
				"Module  SCT3000C02V1 Table"
			::= { sct3000c02v1 1 }

		-- 1.3.6.1.4.1.10106.3.149301.1.1
		sct3000c02v1Entry  OBJECT-TYPE
			SYNTAX Sct3000c02v1Entry
			MAX-ACCESS not-accessible
			STATUS current
			DESCRIPTION
				"Module SCT3000C02V1 Entry"
			INDEX { sct3000c02v1Index }
			::= { sct3000c02v1Table 1 }

			Sct3000c02v1Entry ::=
			SEQUENCE {
				sct3000c02v1Index
				ModuleIndex,
				sct3000c02v1Mode
				ChgOverMode4,
				sct3000c02v1ModeTrapEnable
				AlarmEnable,
				sct3000c02v1Input
				ChgOverInput1,
				sct3000c02v1InputTrapEnable
				AlarmEnable,
				sct3000c02v1Selin0
				Bit0Clo1Open,
				sct3000c02v1Selin1
				Bit0Clo1Open,
				sct3000c02v1SerialNo
				SerialNo
			 }

		-- 1.3.6.1.4.1.10106.3.101291.1.1.1
		sct3000c02v1Index OBJECT-TYPE
			SYNTAX ModuleIndex
			MAX-ACCESS read-only
			STATUS current
			DESCRIPTION
				"Index of SCT3000C02V1 Table"
		::= { sct3000c02v1Entry 1 }

		-- 1.3.6.1.4.1.10106.3.101291.1.1.3
		sct3000c02v1Mode OBJECT-TYPE
			SYNTAX ChgOverMode4
			MAX-ACCESS read-write
			STATUS current
			DESCRIPTION
				"Allows selecting the switching mode"
		::= { sct3000c02v1Entry 3 }

		-- 1.3.6.1.4.1.10106.3.101291.1.1.4
		sct3000c02v1ModeTrapEnable OBJECT-TYPE
			SYNTAX AlarmEnable
			MAX-ACCESS read-write
			STATUS current
			DESCRIPTION
				"Allows selecting the switching mode Trap Enable"
		::= { sct3000c02v1Entry 4 }

		-- 1.3.6.1.4.1.10106.3.101291.1.1.5
		sct3000c02v1Input OBJECT-TYPE
			SYNTAX ChgOverInput1
			MAX-ACCESS read-write
			STATUS current
			DESCRIPTION
				"Selected input"
		::= { sct3000c02v1Entry 5 }

		-- 1.3.6.1.4.1.10106.3.101291.1.1.6
		sct3000c02v1InputTrapEnable OBJECT-TYPE
			SYNTAX AlarmEnable
			MAX-ACCESS read-write
			STATUS current
			DESCRIPTION
				"Selected input Trap Enable"
		::= { sct3000c02v1Entry 6 }

		-- 1.3.6.1.4.1.10106.3.101291.1.1.7
		sct3000c02v1Selin0 OBJECT-TYPE
			SYNTAX Bit0Clo1Open
			MAX-ACCESS read-only
			STATUS current
			DESCRIPTION
				"Status of SELIN0 pin"
		::= { sct3000c02v1Entry 7 }

		-- 1.3.6.1.4.1.10106.3.101291.1.1.9
		sct3000c02v1Selin1 OBJECT-TYPE
			SYNTAX Bit0Clo1Open
			MAX-ACCESS read-only
			STATUS current
			DESCRIPTION
				"Status of SELIN1 pin"
		::= { sct3000c02v1Entry 9 }

		-- 1.3.6.1.4.1.10106.3.101291.1.1.11
		sct3000c02v1SerialNo OBJECT-TYPE
			SYNTAX SerialNo
			MAX-ACCESS read-only
			STATUS current
			DESCRIPTION
				"Serial number"
		::= { sct3000c02v1Entry 11 }

		-- 1.3.6.1.4.1.10106.3.150501
		dat3000p01v1 OBJECT IDENTIFIER ::= { albalaProducts 150501 }

		-- 1.3.6.1.4.1.10106.3.150501.1
		dat3000p01v1Table  OBJECT-TYPE
			SYNTAX SEQUENCE OF Dat3000p01v1Entry
			MAX-ACCESS not-accessible
			STATUS current
			DESCRIPTION
				"Module  DAT3000P01V1 Table"
			::= { dat3000p01v1 1 }

		-- 1.3.6.1.4.1.10106.3.150501.1.1
		dat3000p01v1Entry  OBJECT-TYPE
			SYNTAX Dat3000p01v1Entry
			MAX-ACCESS not-accessible
			STATUS current
			DESCRIPTION
				"Module DAT3000P01V1 Entry"
			INDEX { dat3000p01v1Index }
			::= { dat3000p01v1Table 1 }

			Dat3000p01v1Entry ::=
			SEQUENCE {
				dat3000p01v1Index
				ModuleIndex,
				dat3000p01v1InBits
				Bit020124,
				dat3000p01v1OutBits
				Bit020124,
				dat3000p01v1Mode
				Bit0Aut1Man,
				dat3000p01v1InputRef
				AudioRef1,
				dat3000p01v1OutputFreq
				AudioSelFreq1,
				dat3000p01v1MonoAes1
				Bit0Ste1Mon,
				dat3000p01v1MuteAes1
				Bit0No1Yes,
				dat3000p01v1MonoAes2
				Bit0Ste1Mon,
				dat3000p01v1MuteAes2
				Bit0No1Yes,
				dat3000p01v1DelayPol
				Bit0Nor1Inv,
				dat3000p01v1SyncMode
				Bit0Syn1Del,
				dat3000p01v1In192k
				Bit0No1Yes,
				dat3000p01v1Out192k
				Bit0No1Yes,
				dat3000p01v1FixDelay1
				DelaySamp1,
				dat3000p01v1FixDelay2
				DelaySamp1,
				dat3000p01v1GainAes1A
				Gain24dbMute,
				dat3000p01v1PhaseAes1A
				Bit0Nor1Inv,
				dat3000p01v1GainAes1B
				Gain24dbMute,
				dat3000p01v1PhaseAes1B
				Bit0Nor1Inv,
				dat3000p01v1GainAes2A
				Gain24dbMute,
				dat3000p01v1PhaseAes2A
				Bit0Nor1Inv,
				dat3000p01v1GainAes2B
				Gain24dbMute,
				dat3000p01v1PhaseAes2B
				Bit0Nor1Inv,
				dat3000p01v1Aes1AInput
				AesMxInput1,
				dat3000p01v1Aes1BInput
				AesMxInput1,
				dat3000p01v1Aes2AInput
				AesMxInput1,
				dat3000p01v1Aes2BInput
				AesMxInput1,
				dat3000p01v1OutFreq
				AudioSelFreq2,
				dat3000p01v1LockAes
				BitFailN,
				dat3000p01v1LockAesTrapEnable
				AlarmEnable,
				dat3000p01v1LockVid
				BitFailN,
				dat3000p01v1LockVidTrapEnable
				AlarmEnable,
				dat3000p01v1LockWclk
				BitFailN,
				dat3000p01v1LockWclkTrapEnable
				AlarmEnable,
				dat3000p01v1Aes2DetFreq
				AudioSelFreq3,
				dat3000p01v1Aes1DetFreq
				AudioSelFreq3,
				dat3000p01v1VarDelay1
				DelaySamp1,
				dat3000p01v1VarDelay2
				DelaySamp1,
				dat3000p01v1PeakLevOut1A
				Uint16,
				dat3000p01v1PeakLevOut1B
				Uint16,
				dat3000p01v1PeakLevOut2A
				Uint16,
				dat3000p01v1PeakLevOut2B
				Uint16
			 }

		-- 1.3.6.1.4.1.10106.3.101291.1.1.1
		dat3000p01v1Index OBJECT-TYPE
			SYNTAX ModuleIndex
			MAX-ACCESS read-only
			STATUS current
			DESCRIPTION
				"Index of DAT3000P01V1 Table"
		::= { dat3000p01v1Entry 1 }

		-- 1.3.6.1.4.1.10106.3.101291.1.1.3
		dat3000p01v1InBits OBJECT-TYPE
			SYNTAX Bit020124
			MAX-ACCESS read-write
			STATUS current
			DESCRIPTION
				"Allows selecting the number of bits in inputs"
		::= { dat3000p01v1Entry 3 }

		-- 1.3.6.1.4.1.10106.3.101291.1.1.5
		dat3000p01v1OutBits OBJECT-TYPE
			SYNTAX Bit020124
			MAX-ACCESS read-write
			STATUS current
			DESCRIPTION
				"Allows selecting the number of bits in outputs"
		::= { dat3000p01v1Entry 5 }

		-- 1.3.6.1.4.1.10106.3.101291.1.1.7
		dat3000p01v1Mode OBJECT-TYPE
			SYNTAX Bit0Aut1Man
			MAX-ACCESS read-write
			STATUS current
			DESCRIPTION
				"Allows selecting the reference selection mode"
		::= { dat3000p01v1Entry 7 }

		-- 1.3.6.1.4.1.10106.3.101291.1.1.9
		dat3000p01v1InputRef OBJECT-TYPE
			SYNTAX AudioRef1
			MAX-ACCESS read-write
			STATUS current
			DESCRIPTION
				"Allows selecting the reference input in manual mode"
		::= { dat3000p01v1Entry 9 }

		-- 1.3.6.1.4.1.10106.3.101291.1.1.11
		dat3000p01v1OutputFreq OBJECT-TYPE
			SYNTAX AudioSelFreq1
			MAX-ACCESS read-write
			STATUS current
			DESCRIPTION
				"Allows selecting the output samplign frequency in manual mode"
		::= { dat3000p01v1Entry 11 }

		-- 1.3.6.1.4.1.10106.3.101291.1.1.13
		dat3000p01v1MonoAes1 OBJECT-TYPE
			SYNTAX Bit0Ste1Mon
			MAX-ACCESS read-write
			STATUS current
			DESCRIPTION
				"Allows selecting the AES1 audio type"
		::= { dat3000p01v1Entry 13 }

		-- 1.3.6.1.4.1.10106.3.101291.1.1.15
		dat3000p01v1MuteAes1 OBJECT-TYPE
			SYNTAX Bit0No1Yes
			MAX-ACCESS read-write
			STATUS current
			DESCRIPTION
				"Allows muting AES1"
		::= { dat3000p01v1Entry 15 }

		-- 1.3.6.1.4.1.10106.3.101291.1.1.17
		dat3000p01v1MonoAes2 OBJECT-TYPE
			SYNTAX Bit0Ste1Mon
			MAX-ACCESS read-write
			STATUS current
			DESCRIPTION
				"Allows selecting the AES2 audio type"
		::= { dat3000p01v1Entry 17 }

		-- 1.3.6.1.4.1.10106.3.101291.1.1.19
		dat3000p01v1MuteAes2 OBJECT-TYPE
			SYNTAX Bit0No1Yes
			MAX-ACCESS read-write
			STATUS current
			DESCRIPTION
				"Allows muting AES2"
		::= { dat3000p01v1Entry 19 }

		-- 1.3.6.1.4.1.10106.3.101291.1.1.21
		dat3000p01v1DelayPol OBJECT-TYPE
			SYNTAX Bit0Nor1Inv
			MAX-ACCESS read-write
			STATUS current
			DESCRIPTION
				"Allows selecting the input delay polarity"
		::= { dat3000p01v1Entry 21 }

		-- 1.3.6.1.4.1.10106.3.101291.1.1.23
		dat3000p01v1SyncMode OBJECT-TYPE
			SYNTAX Bit0Syn1Del
			MAX-ACCESS read-write
			STATUS current
			DESCRIPTION
				"Allows selecting the operating mode"
		::= { dat3000p01v1Entry 23 }

		-- 1.3.6.1.4.1.10106.3.101291.1.1.25
		dat3000p01v1In192k OBJECT-TYPE
			SYNTAX Bit0No1Yes
			MAX-ACCESS read-write
			STATUS current
			DESCRIPTION
				"Allows selecting 192kHz input"
		::= { dat3000p01v1Entry 25 }

		-- 1.3.6.1.4.1.10106.3.101291.1.1.27
		dat3000p01v1Out192k OBJECT-TYPE
			SYNTAX Bit0No1Yes
			MAX-ACCESS read-write
			STATUS current
			DESCRIPTION
				"Allows selecting 192kHz output"
		::= { dat3000p01v1Entry 27 }

		-- 1.3.6.1.4.1.10106.3.101291.1.1.29
		dat3000p01v1FixDelay1 OBJECT-TYPE
			SYNTAX DelaySamp1
			MAX-ACCESS read-write
			STATUS current
			DESCRIPTION
				"Allows setting a fixed delay for AES1"
		::= { dat3000p01v1Entry 29 }

		-- 1.3.6.1.4.1.10106.3.101291.1.1.31
		dat3000p01v1FixDelay2 OBJECT-TYPE
			SYNTAX DelaySamp1
			MAX-ACCESS read-write
			STATUS current
			DESCRIPTION
				"Allows setting a fixed delay for AES2"
		::= { dat3000p01v1Entry 31 }

		-- 1.3.6.1.4.1.10106.3.101291.1.1.33
		dat3000p01v1GainAes1A OBJECT-TYPE
			SYNTAX Gain24dbMute
			MAX-ACCESS read-write
			STATUS current
			DESCRIPTION
				"Allows adjusting the gain of AES1 channel A"
		::= { dat3000p01v1Entry 33 }

		-- 1.3.6.1.4.1.10106.3.101291.1.1.35
		dat3000p01v1PhaseAes1A OBJECT-TYPE
			SYNTAX Bit0Nor1Inv
			MAX-ACCESS read-write
			STATUS current
			DESCRIPTION
				"Allows changing the phase of AES1 channel A"
		::= { dat3000p01v1Entry 35 }

		-- 1.3.6.1.4.1.10106.3.101291.1.1.37
		dat3000p01v1GainAes1B OBJECT-TYPE
			SYNTAX Gain24dbMute
			MAX-ACCESS read-write
			STATUS current
			DESCRIPTION
				"Allows adjusting the gain of AES1 channel B"
		::= { dat3000p01v1Entry 37 }

		-- 1.3.6.1.4.1.10106.3.101291.1.1.39
		dat3000p01v1PhaseAes1B OBJECT-TYPE
			SYNTAX Bit0Nor1Inv
			MAX-ACCESS read-write
			STATUS current
			DESCRIPTION
				"Allows changing the phase of AES1 channel B"
		::= { dat3000p01v1Entry 39 }

		-- 1.3.6.1.4.1.10106.3.101291.1.1.41
		dat3000p01v1GainAes2A OBJECT-TYPE
			SYNTAX Gain24dbMute
			MAX-ACCESS read-write
			STATUS current
			DESCRIPTION
				"Allows adjusting the gain of AES2 channel A"
		::= { dat3000p01v1Entry 41 }

		-- 1.3.6.1.4.1.10106.3.101291.1.1.43
		dat3000p01v1PhaseAes2A OBJECT-TYPE
			SYNTAX Bit0Nor1Inv
			MAX-ACCESS read-write
			STATUS current
			DESCRIPTION
				"Allows changing the phase of AES2 channel A"
		::= { dat3000p01v1Entry 43 }

		-- 1.3.6.1.4.1.10106.3.101291.1.1.45
		dat3000p01v1GainAes2B OBJECT-TYPE
			SYNTAX Gain24dbMute
			MAX-ACCESS read-write
			STATUS current
			DESCRIPTION
				"Allows adjusting the gain of AES2 channel B"
		::= { dat3000p01v1Entry 45 }

		-- 1.3.6.1.4.1.10106.3.101291.1.1.47
		dat3000p01v1PhaseAes2B OBJECT-TYPE
			SYNTAX Bit0Nor1Inv
			MAX-ACCESS read-write
			STATUS current
			DESCRIPTION
				"Allows changing the phase of AES2 channel B"
		::= { dat3000p01v1Entry 47 }

		-- 1.3.6.1.4.1.10106.3.101291.1.1.49
		dat3000p01v1Aes1AInput OBJECT-TYPE
			SYNTAX AesMxInput1
			MAX-ACCESS read-write
			STATUS current
			DESCRIPTION
				"Allows selecting the channel that is routed to AES1 channel A"
		::= { dat3000p01v1Entry 49 }

		-- 1.3.6.1.4.1.10106.3.101291.1.1.51
		dat3000p01v1Aes1BInput OBJECT-TYPE
			SYNTAX AesMxInput1
			MAX-ACCESS read-write
			STATUS current
			DESCRIPTION
				"Allows selecting the channel that is routed to AES1 channel B"
		::= { dat3000p01v1Entry 51 }

		-- 1.3.6.1.4.1.10106.3.101291.1.1.53
		dat3000p01v1Aes2AInput OBJECT-TYPE
			SYNTAX AesMxInput1
			MAX-ACCESS read-write
			STATUS current
			DESCRIPTION
				"Allows selecting the channel that is routed to AES2 channel A"
		::= { dat3000p01v1Entry 53 }

		-- 1.3.6.1.4.1.10106.3.101291.1.1.55
		dat3000p01v1Aes2BInput OBJECT-TYPE
			SYNTAX AesMxInput1
			MAX-ACCESS read-write
			STATUS current
			DESCRIPTION
				"Allows selecting the channel that is routed to AES2 channel B"
		::= { dat3000p01v1Entry 55 }

		-- 1.3.6.1.4.1.10106.3.101291.1.1.57
		dat3000p01v1OutFreq OBJECT-TYPE
			SYNTAX AudioSelFreq2
			MAX-ACCESS read-only
			STATUS current
			DESCRIPTION
				"Indicates the actual output sampling frequency"
		::= { dat3000p01v1Entry 57 }

		-- 1.3.6.1.4.1.10106.3.101291.1.1.59
		dat3000p01v1LockAes OBJECT-TYPE
			SYNTAX BitFailN
			MAX-ACCESS read-only
			STATUS current
			DESCRIPTION
				"Indicates AES reference lock"
		::= { dat3000p01v1Entry 59 }

		-- 1.3.6.1.4.1.10106.3.101291.1.1.60
		dat3000p01v1LockAesTrapEnable OBJECT-TYPE
			SYNTAX AlarmEnable
			MAX-ACCESS read-write
			STATUS current
			DESCRIPTION
				"Indicates AES reference lock Trap Enable"
		::= { dat3000p01v1Entry 60 }

		-- 1.3.6.1.4.1.10106.3.101291.1.1.61
		dat3000p01v1LockVid OBJECT-TYPE
			SYNTAX BitFailN
			MAX-ACCESS read-only
			STATUS current
			DESCRIPTION
				"Indicates video reference lock"
		::= { dat3000p01v1Entry 61 }

		-- 1.3.6.1.4.1.10106.3.101291.1.1.62
		dat3000p01v1LockVidTrapEnable OBJECT-TYPE
			SYNTAX AlarmEnable
			MAX-ACCESS read-write
			STATUS current
			DESCRIPTION
				"Indicates video reference lock Trap Enable"
		::= { dat3000p01v1Entry 62 }

		-- 1.3.6.1.4.1.10106.3.101291.1.1.63
		dat3000p01v1LockWclk OBJECT-TYPE
			SYNTAX BitFailN
			MAX-ACCESS read-only
			STATUS current
			DESCRIPTION
				"Indicates Wordclock reference lock"
		::= { dat3000p01v1Entry 63 }

		-- 1.3.6.1.4.1.10106.3.101291.1.1.64
		dat3000p01v1LockWclkTrapEnable OBJECT-TYPE
			SYNTAX AlarmEnable
			MAX-ACCESS read-write
			STATUS current
			DESCRIPTION
				"Indicates Wordclock reference lock Trap Enable"
		::= { dat3000p01v1Entry 64 }

		-- 1.3.6.1.4.1.10106.3.101291.1.1.65
		dat3000p01v1Aes2DetFreq OBJECT-TYPE
			SYNTAX AudioSelFreq3
			MAX-ACCESS read-only
			STATUS current
			DESCRIPTION
				"Indicates the AES1 detected frequency"
		::= { dat3000p01v1Entry 65 }

		-- 1.3.6.1.4.1.10106.3.101291.1.1.67
		dat3000p01v1Aes1DetFreq OBJECT-TYPE
			SYNTAX AudioSelFreq3
			MAX-ACCESS read-only
			STATUS current
			DESCRIPTION
				"Indicates the AES2 detected frequency"
		::= { dat3000p01v1Entry 67 }

		-- 1.3.6.1.4.1.10106.3.101291.1.1.69
		dat3000p01v1VarDelay1 OBJECT-TYPE
			SYNTAX DelaySamp1
			MAX-ACCESS read-only
			STATUS current
			DESCRIPTION
				"Inidcates variable delay AES1"
		::= { dat3000p01v1Entry 69 }

		-- 1.3.6.1.4.1.10106.3.101291.1.1.71
		dat3000p01v1VarDelay2 OBJECT-TYPE
			SYNTAX DelaySamp1
			MAX-ACCESS read-only
			STATUS current
			DESCRIPTION
				"Inidcates variable delay AES2"
		::= { dat3000p01v1Entry 71 }

		-- 1.3.6.1.4.1.10106.3.101291.1.1.73
		dat3000p01v1PeakLevOut1A OBJECT-TYPE
			SYNTAX Uint16
			MAX-ACCESS read-only
			STATUS current
			DESCRIPTION
				"AES1 channel A peak level"
		::= { dat3000p01v1Entry 73 }

		-- 1.3.6.1.4.1.10106.3.101291.1.1.75
		dat3000p01v1PeakLevOut1B OBJECT-TYPE
			SYNTAX Uint16
			MAX-ACCESS read-only
			STATUS current
			DESCRIPTION
				"AES1 channel B peak level"
		::= { dat3000p01v1Entry 75 }

		-- 1.3.6.1.4.1.10106.3.101291.1.1.77
		dat3000p01v1PeakLevOut2A OBJECT-TYPE
			SYNTAX Uint16
			MAX-ACCESS read-only
			STATUS current
			DESCRIPTION
				"AES2 channel A peak level"
		::= { dat3000p01v1Entry 77 }

		-- 1.3.6.1.4.1.10106.3.101291.1.1.79
		dat3000p01v1PeakLevOut2B OBJECT-TYPE
			SYNTAX Uint16
			MAX-ACCESS read-only
			STATUS current
			DESCRIPTION
				"AES2 channel B peak level"
		::= { dat3000p01v1Entry 79 }

		-- 1.3.6.1.4.1.10106.3.157401
		cav3000p01v1 OBJECT IDENTIFIER ::= { albalaProducts 157401 }

		-- 1.3.6.1.4.1.10106.3.157401.1
		cav3000p01v1Table  OBJECT-TYPE
			SYNTAX SEQUENCE OF Cav3000p01v1Entry
			MAX-ACCESS not-accessible
			STATUS current
			DESCRIPTION
				"Module  CAV3000P01V1 Table"
			::= { cav3000p01v1 1 }

		-- 1.3.6.1.4.1.10106.3.157401.1.1
		cav3000p01v1Entry  OBJECT-TYPE
			SYNTAX Cav3000p01v1Entry
			MAX-ACCESS not-accessible
			STATUS current
			DESCRIPTION
				"Module CAV3000P01V1 Entry"
			INDEX { cav3000p01v1Index }
			::= { cav3000p01v1Table 1 }

			Cav3000p01v1Entry ::=
			SEQUENCE {
				cav3000p01v1Index
				ModuleIndex,
				cav3000p01v1AdLines
				Bit05251625,
				cav3000p01v1AdVbiMode
				Bit0Bnk1Pas,
				cav3000p01v1SyncSrc
				Bit0Vid1Ext,
				cav3000p01v1NoAnalog
				BitFail,
				cav3000p01v1NoAnalogTrapEnable
				AlarmEnable,
				cav3000p01v1AnalogUnlock
				BitFail,
				cav3000p01v1AnalogUnlockTrapEnable
				AlarmEnable,
				cav3000p01v1AnalogOvld
				BitFail,
				cav3000p01v1AnalogOvldTrapEnable
				AlarmEnable,
				cav3000p01v1AdFmt
				Bit0Rgb1Ycr
			 }

		-- 1.3.6.1.4.1.10106.3.101291.1.1.1
		cav3000p01v1Index OBJECT-TYPE
			SYNTAX ModuleIndex
			MAX-ACCESS read-only
			STATUS current
			DESCRIPTION
				"Index of CAV3000P01V1 Table"
		::= { cav3000p01v1Entry 1 }

		-- 1.3.6.1.4.1.10106.3.101291.1.1.3
		cav3000p01v1AdLines OBJECT-TYPE
			SYNTAX Bit05251625
			MAX-ACCESS read-write
			STATUS current
			DESCRIPTION
				"AD section TV input signal line number"
		::= { cav3000p01v1Entry 3 }

		-- 1.3.6.1.4.1.10106.3.101291.1.1.5
		cav3000p01v1AdVbiMode OBJECT-TYPE
			SYNTAX Bit0Bnk1Pas
			MAX-ACCESS read-write
			STATUS current
			DESCRIPTION
				"Allows selecting if the AD section VBI is blanked"
		::= { cav3000p01v1Entry 5 }

		-- 1.3.6.1.4.1.10106.3.101291.1.1.7
		cav3000p01v1SyncSrc OBJECT-TYPE
			SYNTAX Bit0Vid1Ext
			MAX-ACCESS read-write
			STATUS current
			DESCRIPTION
				"Allows selecting the sync source"
		::= { cav3000p01v1Entry 7 }

		-- 1.3.6.1.4.1.10106.3.101291.1.1.9
		cav3000p01v1NoAnalog OBJECT-TYPE
			SYNTAX BitFail
			MAX-ACCESS read-only
			STATUS current
			DESCRIPTION
				"Analog componet video signal input status"
		::= { cav3000p01v1Entry 9 }

		-- 1.3.6.1.4.1.10106.3.101291.1.1.10
		cav3000p01v1NoAnalogTrapEnable OBJECT-TYPE
			SYNTAX AlarmEnable
			MAX-ACCESS read-write
			STATUS current
			DESCRIPTION
				"Analog componet video signal input status Trap Enable"
		::= { cav3000p01v1Entry 10 }

		-- 1.3.6.1.4.1.10106.3.101291.1.1.11
		cav3000p01v1AnalogUnlock OBJECT-TYPE
			SYNTAX BitFail
			MAX-ACCESS read-only
			STATUS current
			DESCRIPTION
				"Indicates analog component video signal unlock fail"
		::= { cav3000p01v1Entry 11 }

		-- 1.3.6.1.4.1.10106.3.101291.1.1.12
		cav3000p01v1AnalogUnlockTrapEnable OBJECT-TYPE
			SYNTAX AlarmEnable
			MAX-ACCESS read-write
			STATUS current
			DESCRIPTION
				"Indicates analog component video signal unlock fail Trap Enable"
		::= { cav3000p01v1Entry 12 }

		-- 1.3.6.1.4.1.10106.3.101291.1.1.13
		cav3000p01v1AnalogOvld OBJECT-TYPE
			SYNTAX BitFail
			MAX-ACCESS read-only
			STATUS current
			DESCRIPTION
				"Indicates overload in the A/D converter"
		::= { cav3000p01v1Entry 13 }

		-- 1.3.6.1.4.1.10106.3.101291.1.1.14
		cav3000p01v1AnalogOvldTrapEnable OBJECT-TYPE
			SYNTAX AlarmEnable
			MAX-ACCESS read-write
			STATUS current
			DESCRIPTION
				"Indicates overload in the A/D converter Trap Enable"
		::= { cav3000p01v1Entry 14 }

		-- 1.3.6.1.4.1.10106.3.101291.1.1.15
		cav3000p01v1AdFmt OBJECT-TYPE
			SYNTAX Bit0Rgb1Ycr
			MAX-ACCESS read-only
			STATUS current
			DESCRIPTION
				"Indicates the AD section component format"
		::= { cav3000p01v1Entry 15 }

		-- 1.3.6.1.4.1.10106.3.157501
		cav3001p01v1 OBJECT IDENTIFIER ::= { albalaProducts 157501 }

		-- 1.3.6.1.4.1.10106.3.157501.1
		cav3001p01v1Table  OBJECT-TYPE
			SYNTAX SEQUENCE OF Cav3001p01v1Entry
			MAX-ACCESS not-accessible
			STATUS current
			DESCRIPTION
				"Module  CAV3001P01V1 Table"
			::= { cav3001p01v1 1 }

		-- 1.3.6.1.4.1.10106.3.157501.1.1
		cav3001p01v1Entry  OBJECT-TYPE
			SYNTAX Cav3001p01v1Entry
			MAX-ACCESS not-accessible
			STATUS current
			DESCRIPTION
				"Module CAV3001P01V1 Entry"
			INDEX { cav3001p01v1Index }
			::= { cav3001p01v1Table 1 }

			Cav3001p01v1Entry ::=
			SEQUENCE {
				cav3001p01v1Index
				ModuleIndex,
				cav3001p01v1DaLines
				Bit05251625,
				cav3001p01v1DaVbiMode
				Bit0Bnk1Pas,
				cav3001p01v1NoSdi
				BitFail,
				cav3001p01v1NoSdiTrapEnable
				AlarmEnable,
				cav3001p01v1SdiUnlock
				BitFail,
				cav3001p01v1SdiUnlockTrapEnable
				AlarmEnable,
				cav3001p01v1DaFmt
				Bit0Rgb1Ycr,
				cav3001p01v1EdhFullErr
				BitFail,
				cav3001p01v1EdhFullErrTrapEnable
				AlarmEnable,
				cav3001p01v1EdhActErr
				BitFail,
				cav3001p01v1EdhActErrTrapEnable
				AlarmEnable
			 }

		-- 1.3.6.1.4.1.10106.3.101291.1.1.1
		cav3001p01v1Index OBJECT-TYPE
			SYNTAX ModuleIndex
			MAX-ACCESS read-only
			STATUS current
			DESCRIPTION
				"Index of CAV3001P01V1 Table"
		::= { cav3001p01v1Entry 1 }

		-- 1.3.6.1.4.1.10106.3.101291.1.1.3
		cav3001p01v1DaLines OBJECT-TYPE
			SYNTAX Bit05251625
			MAX-ACCESS read-write
			STATUS current
			DESCRIPTION
				"DA section TV input signal line number"
		::= { cav3001p01v1Entry 3 }

		-- 1.3.6.1.4.1.10106.3.101291.1.1.5
		cav3001p01v1DaVbiMode OBJECT-TYPE
			SYNTAX Bit0Bnk1Pas
			MAX-ACCESS read-write
			STATUS current
			DESCRIPTION
				"Allows selecting if the DA section VBI is blanked"
		::= { cav3001p01v1Entry 5 }

		-- 1.3.6.1.4.1.10106.3.101291.1.1.7
		cav3001p01v1NoSdi OBJECT-TYPE
			SYNTAX BitFail
			MAX-ACCESS read-only
			STATUS current
			DESCRIPTION
				"SDI input signal status"
		::= { cav3001p01v1Entry 7 }

		-- 1.3.6.1.4.1.10106.3.101291.1.1.8
		cav3001p01v1NoSdiTrapEnable OBJECT-TYPE
			SYNTAX AlarmEnable
			MAX-ACCESS read-write
			STATUS current
			DESCRIPTION
				"SDI input signal status Trap Enable"
		::= { cav3001p01v1Entry 8 }

		-- 1.3.6.1.4.1.10106.3.101291.1.1.9
		cav3001p01v1SdiUnlock OBJECT-TYPE
			SYNTAX BitFail
			MAX-ACCESS read-only
			STATUS current
			DESCRIPTION
				"Indicates SDI signal unlock fail"
		::= { cav3001p01v1Entry 9 }

		-- 1.3.6.1.4.1.10106.3.101291.1.1.10
		cav3001p01v1SdiUnlockTrapEnable OBJECT-TYPE
			SYNTAX AlarmEnable
			MAX-ACCESS read-write
			STATUS current
			DESCRIPTION
				"Indicates SDI signal unlock fail Trap Enable"
		::= { cav3001p01v1Entry 10 }

		-- 1.3.6.1.4.1.10106.3.101291.1.1.11
		cav3001p01v1DaFmt OBJECT-TYPE
			SYNTAX Bit0Rgb1Ycr
			MAX-ACCESS read-only
			STATUS current
			DESCRIPTION
				"Indicates the DA section component format"
		::= { cav3001p01v1Entry 11 }

		-- 1.3.6.1.4.1.10106.3.101291.1.1.13
		cav3001p01v1EdhFullErr OBJECT-TYPE
			SYNTAX BitFail
			MAX-ACCESS read-only
			STATUS current
			DESCRIPTION
				"Full field EDH error status"
		::= { cav3001p01v1Entry 13 }

		-- 1.3.6.1.4.1.10106.3.101291.1.1.14
		cav3001p01v1EdhFullErrTrapEnable OBJECT-TYPE
			SYNTAX AlarmEnable
			MAX-ACCESS read-write
			STATUS current
			DESCRIPTION
				"Full field EDH error status Trap Enable"
		::= { cav3001p01v1Entry 14 }

		-- 1.3.6.1.4.1.10106.3.101291.1.1.15
		cav3001p01v1EdhActErr OBJECT-TYPE
			SYNTAX BitFail
			MAX-ACCESS read-only
			STATUS current
			DESCRIPTION
				"Active picture EDH error status"
		::= { cav3001p01v1Entry 15 }

		-- 1.3.6.1.4.1.10106.3.101291.1.1.16
		cav3001p01v1EdhActErrTrapEnable OBJECT-TYPE
			SYNTAX AlarmEnable
			MAX-ACCESS read-write
			STATUS current
			DESCRIPTION
				"Active picture EDH error status Trap Enable"
		::= { cav3001p01v1Entry 16 }

		-- 1.3.6.1.4.1.10106.3.157601
		cav3002p01v1 OBJECT IDENTIFIER ::= { albalaProducts 157601 }

		-- 1.3.6.1.4.1.10106.3.157601.1
		cav3002p01v1Table  OBJECT-TYPE
			SYNTAX SEQUENCE OF Cav3002p01v1Entry
			MAX-ACCESS not-accessible
			STATUS current
			DESCRIPTION
				"Module  CAV3002P01V1 Table"
			::= { cav3002p01v1 1 }

		-- 1.3.6.1.4.1.10106.3.157601.1.1
		cav3002p01v1Entry  OBJECT-TYPE
			SYNTAX Cav3002p01v1Entry
			MAX-ACCESS not-accessible
			STATUS current
			DESCRIPTION
				"Module CAV3002P01V1 Entry"
			INDEX { cav3002p01v1Index }
			::= { cav3002p01v1Table 1 }

			Cav3002p01v1Entry ::=
			SEQUENCE {
				cav3002p01v1Index
				ModuleIndex,
				cav3002p01v1AdLines
				Bit05251625,
				cav3002p01v1AdVbiMode
				Bit0Bnk1Pas,
				cav3002p01v1SyncSrc
				Bit0Vid1Ext,
				cav3002p01v1DaLines
				Bit05251625,
				cav3002p01v1DaVbiMode
				Bit0Bnk1Pas,
				cav3002p01v1NoAnalog
				BitFail,
				cav3002p01v1NoAnalogTrapEnable
				AlarmEnable,
				cav3002p01v1AnalogUnlock
				BitFail,
				cav3002p01v1AnalogUnlockTrapEnable
				AlarmEnable,
				cav3002p01v1AnalogOvld
				BitFail,
				cav3002p01v1AnalogOvldTrapEnable
				AlarmEnable,
				cav3002p01v1AdFmt
				Bit0Rgb1Ycr,
				cav3002p01v1NoSdi
				BitFail,
				cav3002p01v1NoSdiTrapEnable
				AlarmEnable,
				cav3002p01v1SdiUnlock
				BitFail,
				cav3002p01v1SdiUnlockTrapEnable
				AlarmEnable,
				cav3002p01v1DaFmt
				Bit0Rgb1Ycr,
				cav3002p01v1EdhFullErr
				BitFail,
				cav3002p01v1EdhFullErrTrapEnable
				AlarmEnable,
				cav3002p01v1EdhActErr
				BitFail,
				cav3002p01v1EdhActErrTrapEnable
				AlarmEnable
			 }

		-- 1.3.6.1.4.1.10106.3.101291.1.1.1
		cav3002p01v1Index OBJECT-TYPE
			SYNTAX ModuleIndex
			MAX-ACCESS read-only
			STATUS current
			DESCRIPTION
				"Index of CAV3002P01V1 Table"
		::= { cav3002p01v1Entry 1 }

		-- 1.3.6.1.4.1.10106.3.101291.1.1.3
		cav3002p01v1AdLines OBJECT-TYPE
			SYNTAX Bit05251625
			MAX-ACCESS read-write
			STATUS current
			DESCRIPTION
				"AD section TV input signal line number"
		::= { cav3002p01v1Entry 3 }

		-- 1.3.6.1.4.1.10106.3.101291.1.1.5
		cav3002p01v1AdVbiMode OBJECT-TYPE
			SYNTAX Bit0Bnk1Pas
			MAX-ACCESS read-write
			STATUS current
			DESCRIPTION
				"Allows selecting if the AD section VBI is blanked"
		::= { cav3002p01v1Entry 5 }

		-- 1.3.6.1.4.1.10106.3.101291.1.1.7
		cav3002p01v1SyncSrc OBJECT-TYPE
			SYNTAX Bit0Vid1Ext
			MAX-ACCESS read-write
			STATUS current
			DESCRIPTION
				"Allows selecting the sync source"
		::= { cav3002p01v1Entry 7 }

		-- 1.3.6.1.4.1.10106.3.101291.1.1.9
		cav3002p01v1DaLines OBJECT-TYPE
			SYNTAX Bit05251625
			MAX-ACCESS read-write
			STATUS current
			DESCRIPTION
				"DA section TV input signal line number"
		::= { cav3002p01v1Entry 9 }

		-- 1.3.6.1.4.1.10106.3.101291.1.1.11
		cav3002p01v1DaVbiMode OBJECT-TYPE
			SYNTAX Bit0Bnk1Pas
			MAX-ACCESS read-write
			STATUS current
			DESCRIPTION
				"Allows selecting if the DA section VBI is blanked"
		::= { cav3002p01v1Entry 11 }

		-- 1.3.6.1.4.1.10106.3.101291.1.1.13
		cav3002p01v1NoAnalog OBJECT-TYPE
			SYNTAX BitFail
			MAX-ACCESS read-only
			STATUS current
			DESCRIPTION
				"Analog componet video signal input status"
		::= { cav3002p01v1Entry 13 }

		-- 1.3.6.1.4.1.10106.3.101291.1.1.14
		cav3002p01v1NoAnalogTrapEnable OBJECT-TYPE
			SYNTAX AlarmEnable
			MAX-ACCESS read-write
			STATUS current
			DESCRIPTION
				"Analog componet video signal input status Trap Enable"
		::= { cav3002p01v1Entry 14 }

		-- 1.3.6.1.4.1.10106.3.101291.1.1.15
		cav3002p01v1AnalogUnlock OBJECT-TYPE
			SYNTAX BitFail
			MAX-ACCESS read-only
			STATUS current
			DESCRIPTION
				"Indicates analog component video signal unlock fail"
		::= { cav3002p01v1Entry 15 }

		-- 1.3.6.1.4.1.10106.3.101291.1.1.16
		cav3002p01v1AnalogUnlockTrapEnable OBJECT-TYPE
			SYNTAX AlarmEnable
			MAX-ACCESS read-write
			STATUS current
			DESCRIPTION
				"Indicates analog component video signal unlock fail Trap Enable"
		::= { cav3002p01v1Entry 16 }

		-- 1.3.6.1.4.1.10106.3.101291.1.1.17
		cav3002p01v1AnalogOvld OBJECT-TYPE
			SYNTAX BitFail
			MAX-ACCESS read-only
			STATUS current
			DESCRIPTION
				"Indicates overload in the A/D converter"
		::= { cav3002p01v1Entry 17 }

		-- 1.3.6.1.4.1.10106.3.101291.1.1.18
		cav3002p01v1AnalogOvldTrapEnable OBJECT-TYPE
			SYNTAX AlarmEnable
			MAX-ACCESS read-write
			STATUS current
			DESCRIPTION
				"Indicates overload in the A/D converter Trap Enable"
		::= { cav3002p01v1Entry 18 }

		-- 1.3.6.1.4.1.10106.3.101291.1.1.19
		cav3002p01v1AdFmt OBJECT-TYPE
			SYNTAX Bit0Rgb1Ycr
			MAX-ACCESS read-only
			STATUS current
			DESCRIPTION
				"Indicates the AD section component format"
		::= { cav3002p01v1Entry 19 }

		-- 1.3.6.1.4.1.10106.3.101291.1.1.21
		cav3002p01v1NoSdi OBJECT-TYPE
			SYNTAX BitFail
			MAX-ACCESS read-only
			STATUS current
			DESCRIPTION
				"SDI input signal status"
		::= { cav3002p01v1Entry 21 }

		-- 1.3.6.1.4.1.10106.3.101291.1.1.22
		cav3002p01v1NoSdiTrapEnable OBJECT-TYPE
			SYNTAX AlarmEnable
			MAX-ACCESS read-write
			STATUS current
			DESCRIPTION
				"SDI input signal status Trap Enable"
		::= { cav3002p01v1Entry 22 }

		-- 1.3.6.1.4.1.10106.3.101291.1.1.23
		cav3002p01v1SdiUnlock OBJECT-TYPE
			SYNTAX BitFail
			MAX-ACCESS read-only
			STATUS current
			DESCRIPTION
				"Indicates SDI signal unlock fail"
		::= { cav3002p01v1Entry 23 }

		-- 1.3.6.1.4.1.10106.3.101291.1.1.24
		cav3002p01v1SdiUnlockTrapEnable OBJECT-TYPE
			SYNTAX AlarmEnable
			MAX-ACCESS read-write
			STATUS current
			DESCRIPTION
				"Indicates SDI signal unlock fail Trap Enable"
		::= { cav3002p01v1Entry 24 }

		-- 1.3.6.1.4.1.10106.3.101291.1.1.25
		cav3002p01v1DaFmt OBJECT-TYPE
			SYNTAX Bit0Rgb1Ycr
			MAX-ACCESS read-only
			STATUS current
			DESCRIPTION
				"Indicates the DA section component format"
		::= { cav3002p01v1Entry 25 }

		-- 1.3.6.1.4.1.10106.3.101291.1.1.27
		cav3002p01v1EdhFullErr OBJECT-TYPE
			SYNTAX BitFail
			MAX-ACCESS read-only
			STATUS current
			DESCRIPTION
				"Full field EDH error status"
		::= { cav3002p01v1Entry 27 }

		-- 1.3.6.1.4.1.10106.3.101291.1.1.28
		cav3002p01v1EdhFullErrTrapEnable OBJECT-TYPE
			SYNTAX AlarmEnable
			MAX-ACCESS read-write
			STATUS current
			DESCRIPTION
				"Full field EDH error status Trap Enable"
		::= { cav3002p01v1Entry 28 }

		-- 1.3.6.1.4.1.10106.3.101291.1.1.29
		cav3002p01v1EdhActErr OBJECT-TYPE
			SYNTAX BitFail
			MAX-ACCESS read-only
			STATUS current
			DESCRIPTION
				"Active picture EDH error status"
		::= { cav3002p01v1Entry 29 }

		-- 1.3.6.1.4.1.10106.3.101291.1.1.30
		cav3002p01v1EdhActErrTrapEnable OBJECT-TYPE
			SYNTAX AlarmEnable
			MAX-ACCESS read-write
			STATUS current
			DESCRIPTION
				"Active picture EDH error status Trap Enable"
		::= { cav3002p01v1Entry 30 }

		-- 1.3.6.1.4.1.10106.3.162801
		dsw3000c03v1 OBJECT IDENTIFIER ::= { albalaProducts 162801 }

		-- 1.3.6.1.4.1.10106.3.162801.1
		dsw3000c03v1Table  OBJECT-TYPE
			SYNTAX SEQUENCE OF Dsw3000c03v1Entry
			MAX-ACCESS not-accessible
			STATUS current
			DESCRIPTION
				"Module  DSW3000C03V1 Table"
			::= { dsw3000c03v1 1 }

		-- 1.3.6.1.4.1.10106.3.162801.1.1
		dsw3000c03v1Entry  OBJECT-TYPE
			SYNTAX Dsw3000c03v1Entry
			MAX-ACCESS not-accessible
			STATUS current
			DESCRIPTION
				"Module DSW3000C03V1 Entry"
			INDEX { dsw3000c03v1Index }
			::= { dsw3000c03v1Table 1 }

			Dsw3000c03v1Entry ::=
			SEQUENCE {
				dsw3000c03v1Index
				ModuleIndex,
				dsw3000c03v1Mode
				ChgOverMode2,
				dsw3000c03v1ModeTrapEnable
				AlarmEnable,
				dsw3000c03v1Buzzer
				BitMask,
				dsw3000c03v1Input
				ChgOverInput1,
				dsw3000c03v1InputTrapEnable
				AlarmEnable,
				dsw3000c03v1MainFail
				BitFail,
				dsw3000c03v1MainFailTrapEnable
				AlarmEnable,
				dsw3000c03v1ExtMainFail
				BitFail,
				dsw3000c03v1ExtMainFailTrapEnable
				AlarmEnable,
				dsw3000c03v1ResFail
				BitFail,
				dsw3000c03v1ResFailTrapEnable
				AlarmEnable,
				dsw3000c03v1ExtResFail
				BitFail,
				dsw3000c03v1ExtResFailTrapEnable
				AlarmEnable,
				dsw3000c03v1AuxFail
				BitFail,
				dsw3000c03v1AuxFailTrapEnable
				AlarmEnable,
				dsw3000c03v1ExtAuxFail
				BitFail,
				dsw3000c03v1ExtAuxFailTrapEnable
				AlarmEnable
			 }

		-- 1.3.6.1.4.1.10106.3.101291.1.1.1
		dsw3000c03v1Index OBJECT-TYPE
			SYNTAX ModuleIndex
			MAX-ACCESS read-only
			STATUS current
			DESCRIPTION
				"Index of DSW3000C03V1 Table"
		::= { dsw3000c03v1Entry 1 }

		-- 1.3.6.1.4.1.10106.3.101291.1.1.3
		dsw3000c03v1Mode OBJECT-TYPE
			SYNTAX ChgOverMode2
			MAX-ACCESS read-write
			STATUS current
			DESCRIPTION
				"Allows selecting the switching mode"
		::= { dsw3000c03v1Entry 3 }

		-- 1.3.6.1.4.1.10106.3.101291.1.1.4
		dsw3000c03v1ModeTrapEnable OBJECT-TYPE
			SYNTAX AlarmEnable
			MAX-ACCESS read-write
			STATUS current
			DESCRIPTION
				"Allows selecting the switching mode Trap Enable"
		::= { dsw3000c03v1Entry 4 }

		-- 1.3.6.1.4.1.10106.3.101291.1.1.5
		dsw3000c03v1Buzzer OBJECT-TYPE
			SYNTAX BitMask
			MAX-ACCESS read-write
			STATUS current
			DESCRIPTION
				"Allows buzzer operation"
		::= { dsw3000c03v1Entry 5 }

		-- 1.3.6.1.4.1.10106.3.101291.1.1.7
		dsw3000c03v1Input OBJECT-TYPE
			SYNTAX ChgOverInput1
			MAX-ACCESS read-write
			STATUS current
			DESCRIPTION
				"Selected input"
		::= { dsw3000c03v1Entry 7 }

		-- 1.3.6.1.4.1.10106.3.101291.1.1.8
		dsw3000c03v1InputTrapEnable OBJECT-TYPE
			SYNTAX AlarmEnable
			MAX-ACCESS read-write
			STATUS current
			DESCRIPTION
				"Selected input Trap Enable"
		::= { dsw3000c03v1Entry 8 }

		-- 1.3.6.1.4.1.10106.3.101291.1.1.9
		dsw3000c03v1MainFail OBJECT-TYPE
			SYNTAX BitFail
			MAX-ACCESS read-only
			STATUS current
			DESCRIPTION
				"Main input status"
		::= { dsw3000c03v1Entry 9 }

		-- 1.3.6.1.4.1.10106.3.101291.1.1.10
		dsw3000c03v1MainFailTrapEnable OBJECT-TYPE
			SYNTAX AlarmEnable
			MAX-ACCESS read-write
			STATUS current
			DESCRIPTION
				"Main input status Trap Enable"
		::= { dsw3000c03v1Entry 10 }

		-- 1.3.6.1.4.1.10106.3.101291.1.1.11
		dsw3000c03v1ExtMainFail OBJECT-TYPE
			SYNTAX BitFail
			MAX-ACCESS read-only
			STATUS current
			DESCRIPTION
				"Main external input fail status"
		::= { dsw3000c03v1Entry 11 }

		-- 1.3.6.1.4.1.10106.3.101291.1.1.12
		dsw3000c03v1ExtMainFailTrapEnable OBJECT-TYPE
			SYNTAX AlarmEnable
			MAX-ACCESS read-write
			STATUS current
			DESCRIPTION
				"Main external input fail status Trap Enable"
		::= { dsw3000c03v1Entry 12 }

		-- 1.3.6.1.4.1.10106.3.101291.1.1.13
		dsw3000c03v1ResFail OBJECT-TYPE
			SYNTAX BitFail
			MAX-ACCESS read-only
			STATUS current
			DESCRIPTION
				"Reserve input status"
		::= { dsw3000c03v1Entry 13 }

		-- 1.3.6.1.4.1.10106.3.101291.1.1.14
		dsw3000c03v1ResFailTrapEnable OBJECT-TYPE
			SYNTAX AlarmEnable
			MAX-ACCESS read-write
			STATUS current
			DESCRIPTION
				"Reserve input status Trap Enable"
		::= { dsw3000c03v1Entry 14 }

		-- 1.3.6.1.4.1.10106.3.101291.1.1.15
		dsw3000c03v1ExtResFail OBJECT-TYPE
			SYNTAX BitFail
			MAX-ACCESS read-only
			STATUS current
			DESCRIPTION
				"Reserve external input fail status"
		::= { dsw3000c03v1Entry 15 }

		-- 1.3.6.1.4.1.10106.3.101291.1.1.16
		dsw3000c03v1ExtResFailTrapEnable OBJECT-TYPE
			SYNTAX AlarmEnable
			MAX-ACCESS read-write
			STATUS current
			DESCRIPTION
				"Reserve external input fail status Trap Enable"
		::= { dsw3000c03v1Entry 16 }

		-- 1.3.6.1.4.1.10106.3.101291.1.1.17
		dsw3000c03v1AuxFail OBJECT-TYPE
			SYNTAX BitFail
			MAX-ACCESS read-only
			STATUS current
			DESCRIPTION
				"Auxiliar input status"
		::= { dsw3000c03v1Entry 17 }

		-- 1.3.6.1.4.1.10106.3.101291.1.1.18
		dsw3000c03v1AuxFailTrapEnable OBJECT-TYPE
			SYNTAX AlarmEnable
			MAX-ACCESS read-write
			STATUS current
			DESCRIPTION
				"Auxiliar input status Trap Enable"
		::= { dsw3000c03v1Entry 18 }

		-- 1.3.6.1.4.1.10106.3.101291.1.1.19
		dsw3000c03v1ExtAuxFail OBJECT-TYPE
			SYNTAX BitFail
			MAX-ACCESS read-only
			STATUS current
			DESCRIPTION
				"Auxiliar external input fail status"
		::= { dsw3000c03v1Entry 19 }

		-- 1.3.6.1.4.1.10106.3.101291.1.1.20
		dsw3000c03v1ExtAuxFailTrapEnable OBJECT-TYPE
			SYNTAX AlarmEnable
			MAX-ACCESS read-write
			STATUS current
			DESCRIPTION
				"Auxiliar external input fail status Trap Enable"
		::= { dsw3000c03v1Entry 20 }

		-- 1.3.6.1.4.1.10106.3.163501
		eap3000p01v1 OBJECT IDENTIFIER ::= { albalaProducts 163501 }

		-- 1.3.6.1.4.1.10106.3.163501.1
		eap3000p01v1Table  OBJECT-TYPE
			SYNTAX SEQUENCE OF Eap3000p01v1Entry
			MAX-ACCESS not-accessible
			STATUS current
			DESCRIPTION
				"Module  EAP3000P01V1 Table"
			::= { eap3000p01v1 1 }

		-- 1.3.6.1.4.1.10106.3.163501.1.1
		eap3000p01v1Entry  OBJECT-TYPE
			SYNTAX Eap3000p01v1Entry
			MAX-ACCESS not-accessible
			STATUS current
			DESCRIPTION
				"Module EAP3000P01V1 Entry"
			INDEX { eap3000p01v1Index }
			::= { eap3000p01v1Table 1 }

			Eap3000p01v1Entry ::=
			SEQUENCE {
				eap3000p01v1Index
				ModuleIndex,
				eap3000p01v1ActivePreset
				PresetActive,
				eap3000p01v1LoadPreset
				PresetLoad,
				eap3000p01v1SavePreset
				PresetSave,
				eap3000p01v1GainCh1
				Gain24dbMute,
				eap3000p01v1PhaseCh1
				Bit0Nor1Inv,
				eap3000p01v1GainCh2
				Gain24dbMute,
				eap3000p01v1PhaseCh2
				Bit0Nor1Inv,
				eap3000p01v1GainCh3
				Gain24dbMute,
				eap3000p01v1PhaseCh3
				Bit0Nor1Inv,
				eap3000p01v1GainCh4
				Gain24dbMute,
				eap3000p01v1PhaseCh4
				Bit0Nor1Inv,
				eap3000p01v1Ch1Input
				GrpMxInput1,
				eap3000p01v1Ch2Input
				GrpMxInput1,
				eap3000p01v1Ch3Input
				GrpMxInput1,
				eap3000p01v1Ch4Input
				GrpMxInput1,
				eap3000p01v1StCh1Input
				GrpMxInput1,
				eap3000p01v1StCh2Input
				GrpMxInput1,
				eap3000p01v1StCh3Input
				GrpMxInput1,
				eap3000p01v1StCh4Input
				GrpMxInput1,
				eap3000p01v1MuteCh1
				Bit0No1Yes,
				eap3000p01v1MuteCh2
				Bit0No1Yes,
				eap3000p01v1MuteCh3
				Bit0No1Yes,
				eap3000p01v1MuteCh4
				Bit0No1Yes,
				eap3000p01v1AddCh1Ch2
				Bit0No1Yes,
				eap3000p01v1AddCh3Ch4
				Bit0No1Yes,
				eap3000p01v1GroupProcess
				EmbedGroup,
				eap3000p01v1HideVu
				Bit0No1Yes,
				eap3000p01v1HideStat
				Bit0No1Yes,
				eap3000p01v1ShowControl
				Bit0No1Yes,
				eap3000p01v1PeakHold
				Bit0No1Yes,
				eap3000p01v1Process
				Bit0Yes1No,
				eap3000p01v1SelMeasure
				Bit0In1Out,
				eap3000p01v1GroupMeasure
				EmbedGroup,
				eap3000p01v1OverloadLevel
				LevelDbfs1,
				eap3000p01v1SilenceLevel
				LevelDbfs1,
				eap3000p01v1SilenceTime
				TimeS2,
				eap3000p01v1NoSig
				BitFail,
				eap3000p01v1NoSigTrapEnable
				AlarmEnable,
				eap3000p01v1MaxEq
				BitFail,
				eap3000p01v1EdhErr
				BitFail,
				eap3000p01v1PckAGr1
				Bit0No1Yes,
				eap3000p01v1PckAGr2
				Bit0No1Yes,
				eap3000p01v1PckAGr3
				Bit0No1Yes,
				eap3000p01v1PckAGr4
				Bit0No1Yes,
				eap3000p01v1VuLevCh1
				LevelDbfs1,
				eap3000p01v1VuLevCh2
				LevelDbfs1,
				eap3000p01v1VuLevCh3
				LevelDbfs1,
				eap3000p01v1VuLevCh4
				LevelDbfs1,
				eap3000p01v1PeakLevCh1
				LevelDbfs1,
				eap3000p01v1PeakLevCh2
				LevelDbfs1,
				eap3000p01v1PeakLevCh3
				LevelDbfs1,
				eap3000p01v1PeakLevCh4
				LevelDbfs1,
				eap3000p01v1Antiph12
				BitFail,
				eap3000p01v1Antiph12TrapEnable
				AlarmEnable,
				eap3000p01v1Antiph34
				BitFail,
				eap3000p01v1Antiph34TrapEnable
				AlarmEnable,
				eap3000p01v1SilCh1
				BitFail,
				eap3000p01v1SilCh1TrapEnable
				AlarmEnable,
				eap3000p01v1SilCh2
				BitFail,
				eap3000p01v1SilCh2TrapEnable
				AlarmEnable,
				eap3000p01v1SilCh3
				BitFail,
				eap3000p01v1SilCh3TrapEnable
				AlarmEnable,
				eap3000p01v1SilCh4
				BitFail,
				eap3000p01v1SilCh4TrapEnable
				AlarmEnable,
				eap3000p01v1OvlCh1
				BitFail,
				eap3000p01v1OvlCh1TrapEnable
				AlarmEnable,
				eap3000p01v1OvlCh2
				BitFail,
				eap3000p01v1OvlCh2TrapEnable
				AlarmEnable,
				eap3000p01v1OvlCh3
				BitFail,
				eap3000p01v1OvlCh3TrapEnable
				AlarmEnable,
				eap3000p01v1OvlCh4
				BitFail,
				eap3000p01v1OvlCh4TrapEnable
				AlarmEnable
			 }

		-- 1.3.6.1.4.1.10106.3.101291.1.1.1
		eap3000p01v1Index OBJECT-TYPE
			SYNTAX ModuleIndex
			MAX-ACCESS read-only
			STATUS current
			DESCRIPTION
				"Index of EAP3000P01V1 Table"
		::= { eap3000p01v1Entry 1 }

		-- 1.3.6.1.4.1.10106.3.101291.1.1.3
		eap3000p01v1ActivePreset OBJECT-TYPE
			SYNTAX PresetActive
			MAX-ACCESS read-only
			STATUS current
			DESCRIPTION
				"Shows the active preset"
		::= { eap3000p01v1Entry 3 }

		-- 1.3.6.1.4.1.10106.3.101291.1.1.5
		eap3000p01v1LoadPreset OBJECT-TYPE
			SYNTAX PresetLoad
			MAX-ACCESS read-write
			STATUS current
			DESCRIPTION
				"Allows loading a preset"
		::= { eap3000p01v1Entry 5 }

		-- 1.3.6.1.4.1.10106.3.101291.1.1.7
		eap3000p01v1SavePreset OBJECT-TYPE
			SYNTAX PresetSave
			MAX-ACCESS read-write
			STATUS current
			DESCRIPTION
				"Allows saving a preset"
		::= { eap3000p01v1Entry 7 }

		-- 1.3.6.1.4.1.10106.3.101291.1.1.9
		eap3000p01v1GainCh1 OBJECT-TYPE
			SYNTAX Gain24dbMute
			MAX-ACCESS read-write
			STATUS current
			DESCRIPTION
				"Allows adjusting the gain of channel 1"
		::= { eap3000p01v1Entry 9 }

		-- 1.3.6.1.4.1.10106.3.101291.1.1.11
		eap3000p01v1PhaseCh1 OBJECT-TYPE
			SYNTAX Bit0Nor1Inv
			MAX-ACCESS read-write
			STATUS current
			DESCRIPTION
				"Allows changing the phase of channel 1"
		::= { eap3000p01v1Entry 11 }

		-- 1.3.6.1.4.1.10106.3.101291.1.1.13
		eap3000p01v1GainCh2 OBJECT-TYPE
			SYNTAX Gain24dbMute
			MAX-ACCESS read-write
			STATUS current
			DESCRIPTION
				"Allows adjusting the gain of channel 2"
		::= { eap3000p01v1Entry 13 }

		-- 1.3.6.1.4.1.10106.3.101291.1.1.15
		eap3000p01v1PhaseCh2 OBJECT-TYPE
			SYNTAX Bit0Nor1Inv
			MAX-ACCESS read-write
			STATUS current
			DESCRIPTION
				"Allows changing the phase of channel 2"
		::= { eap3000p01v1Entry 15 }

		-- 1.3.6.1.4.1.10106.3.101291.1.1.17
		eap3000p01v1GainCh3 OBJECT-TYPE
			SYNTAX Gain24dbMute
			MAX-ACCESS read-write
			STATUS current
			DESCRIPTION
				"Allows adjusting the gain of channel 3"
		::= { eap3000p01v1Entry 17 }

		-- 1.3.6.1.4.1.10106.3.101291.1.1.19
		eap3000p01v1PhaseCh3 OBJECT-TYPE
			SYNTAX Bit0Nor1Inv
			MAX-ACCESS read-write
			STATUS current
			DESCRIPTION
				"Allows changing the phase of channel 3"
		::= { eap3000p01v1Entry 19 }

		-- 1.3.6.1.4.1.10106.3.101291.1.1.21
		eap3000p01v1GainCh4 OBJECT-TYPE
			SYNTAX Gain24dbMute
			MAX-ACCESS read-write
			STATUS current
			DESCRIPTION
				"Allows adjusting the gain of channel 4"
		::= { eap3000p01v1Entry 21 }

		-- 1.3.6.1.4.1.10106.3.101291.1.1.23
		eap3000p01v1PhaseCh4 OBJECT-TYPE
			SYNTAX Bit0Nor1Inv
			MAX-ACCESS read-write
			STATUS current
			DESCRIPTION
				"Allows changing the phase of channel 4"
		::= { eap3000p01v1Entry 23 }

		-- 1.3.6.1.4.1.10106.3.101291.1.1.25
		eap3000p01v1Ch1Input OBJECT-TYPE
			SYNTAX GrpMxInput1
			MAX-ACCESS read-write
			STATUS current
			DESCRIPTION
				"Allows selecting audio channel that is routed channel 1"
		::= { eap3000p01v1Entry 25 }

		-- 1.3.6.1.4.1.10106.3.101291.1.1.27
		eap3000p01v1Ch2Input OBJECT-TYPE
			SYNTAX GrpMxInput1
			MAX-ACCESS read-write
			STATUS current
			DESCRIPTION
				"Allows selecting audio channel that is routed channel 2"
		::= { eap3000p01v1Entry 27 }

		-- 1.3.6.1.4.1.10106.3.101291.1.1.29
		eap3000p01v1Ch3Input OBJECT-TYPE
			SYNTAX GrpMxInput1
			MAX-ACCESS read-write
			STATUS current
			DESCRIPTION
				"Allows selecting audio channel that is routed channel 3"
		::= { eap3000p01v1Entry 29 }

		-- 1.3.6.1.4.1.10106.3.101291.1.1.31
		eap3000p01v1Ch4Input OBJECT-TYPE
			SYNTAX GrpMxInput1
			MAX-ACCESS read-write
			STATUS current
			DESCRIPTION
				"Allows selecting audio channel that is routed channel 4"
		::= { eap3000p01v1Entry 31 }

		-- 1.3.6.1.4.1.10106.3.101291.1.1.33
		eap3000p01v1StCh1Input OBJECT-TYPE
			SYNTAX GrpMxInput1
			MAX-ACCESS read-write
			STATUS current
			DESCRIPTION
				"Allows selecting status audio channel that is routed channel 1"
		::= { eap3000p01v1Entry 33 }

		-- 1.3.6.1.4.1.10106.3.101291.1.1.35
		eap3000p01v1StCh2Input OBJECT-TYPE
			SYNTAX GrpMxInput1
			MAX-ACCESS read-write
			STATUS current
			DESCRIPTION
				"Allows selecting status audio channel that is routed channel 2"
		::= { eap3000p01v1Entry 35 }

		-- 1.3.6.1.4.1.10106.3.101291.1.1.37
		eap3000p01v1StCh3Input OBJECT-TYPE
			SYNTAX GrpMxInput1
			MAX-ACCESS read-write
			STATUS current
			DESCRIPTION
				"Allows selecting status audio channel that is routed channel 3"
		::= { eap3000p01v1Entry 37 }

		-- 1.3.6.1.4.1.10106.3.101291.1.1.39
		eap3000p01v1StCh4Input OBJECT-TYPE
			SYNTAX GrpMxInput1
			MAX-ACCESS read-write
			STATUS current
			DESCRIPTION
				"Allows selecting status audio channel that is routed channel 4"
		::= { eap3000p01v1Entry 39 }

		-- 1.3.6.1.4.1.10106.3.101291.1.1.41
		eap3000p01v1MuteCh1 OBJECT-TYPE
			SYNTAX Bit0No1Yes
			MAX-ACCESS read-write
			STATUS current
			DESCRIPTION
				"Mute channel 1"
		::= { eap3000p01v1Entry 41 }

		-- 1.3.6.1.4.1.10106.3.101291.1.1.43
		eap3000p01v1MuteCh2 OBJECT-TYPE
			SYNTAX Bit0No1Yes
			MAX-ACCESS read-write
			STATUS current
			DESCRIPTION
				"Mute channel 2"
		::= { eap3000p01v1Entry 43 }

		-- 1.3.6.1.4.1.10106.3.101291.1.1.45
		eap3000p01v1MuteCh3 OBJECT-TYPE
			SYNTAX Bit0No1Yes
			MAX-ACCESS read-write
			STATUS current
			DESCRIPTION
				"Mute channel 3"
		::= { eap3000p01v1Entry 45 }

		-- 1.3.6.1.4.1.10106.3.101291.1.1.47
		eap3000p01v1MuteCh4 OBJECT-TYPE
			SYNTAX Bit0No1Yes
			MAX-ACCESS read-write
			STATUS current
			DESCRIPTION
				"Mute channel 4"
		::= { eap3000p01v1Entry 47 }

		-- 1.3.6.1.4.1.10106.3.101291.1.1.49
		eap3000p01v1AddCh1Ch2 OBJECT-TYPE
			SYNTAX Bit0No1Yes
			MAX-ACCESS read-write
			STATUS current
			DESCRIPTION
				"Add channel 1 and channel 2"
		::= { eap3000p01v1Entry 49 }

		-- 1.3.6.1.4.1.10106.3.101291.1.1.51
		eap3000p01v1AddCh3Ch4 OBJECT-TYPE
			SYNTAX Bit0No1Yes
			MAX-ACCESS read-write
			STATUS current
			DESCRIPTION
				"Add channel 3 and channel 3"
		::= { eap3000p01v1Entry 51 }

		-- 1.3.6.1.4.1.10106.3.101291.1.1.53
		eap3000p01v1GroupProcess OBJECT-TYPE
			SYNTAX EmbedGroup
			MAX-ACCESS read-write
			STATUS current
			DESCRIPTION
				"Allows selecting the group in which the audio is processed"
		::= { eap3000p01v1Entry 53 }

		-- 1.3.6.1.4.1.10106.3.101291.1.1.55
		eap3000p01v1HideVu OBJECT-TYPE
			SYNTAX Bit0No1Yes
			MAX-ACCESS read-write
			STATUS current
			DESCRIPTION
				"Allows selecting the VU meters not to be shown in the video"
		::= { eap3000p01v1Entry 55 }

		-- 1.3.6.1.4.1.10106.3.101291.1.1.57
		eap3000p01v1HideStat OBJECT-TYPE
			SYNTAX Bit0No1Yes
			MAX-ACCESS read-write
			STATUS current
			DESCRIPTION
				"Allows selecting the status not to be shown in the video"
		::= { eap3000p01v1Entry 57 }

		-- 1.3.6.1.4.1.10106.3.101291.1.1.59
		eap3000p01v1ShowControl OBJECT-TYPE
			SYNTAX Bit0No1Yes
			MAX-ACCESS read-write
			STATUS current
			DESCRIPTION
				"Allows selecting the gain control to be shown in the video"
		::= { eap3000p01v1Entry 59 }

		-- 1.3.6.1.4.1.10106.3.101291.1.1.61
		eap3000p01v1PeakHold OBJECT-TYPE
			SYNTAX Bit0No1Yes
			MAX-ACCESS read-write
			STATUS current
			DESCRIPTION
				"Allows selecting the peak hold when measuring the level"
		::= { eap3000p01v1Entry 61 }

		-- 1.3.6.1.4.1.10106.3.101291.1.1.63
		eap3000p01v1Process OBJECT-TYPE
			SYNTAX Bit0Yes1No
			MAX-ACCESS read-write
			STATUS current
			DESCRIPTION
				"Allows processing the audio"
		::= { eap3000p01v1Entry 63 }

		-- 1.3.6.1.4.1.10106.3.101291.1.1.65
		eap3000p01v1SelMeasure OBJECT-TYPE
			SYNTAX Bit0In1Out
			MAX-ACCESS read-write
			STATUS current
			DESCRIPTION
				"Allows selecting the point in which the measure is performed"
		::= { eap3000p01v1Entry 65 }

		-- 1.3.6.1.4.1.10106.3.101291.1.1.67
		eap3000p01v1GroupMeasure OBJECT-TYPE
			SYNTAX EmbedGroup
			MAX-ACCESS read-write
			STATUS current
			DESCRIPTION
				"Allows selecting the group from which the audio is measured"
		::= { eap3000p01v1Entry 67 }

		-- 1.3.6.1.4.1.10106.3.101291.1.1.69
		eap3000p01v1OverloadLevel OBJECT-TYPE
			SYNTAX LevelDbfs1
			MAX-ACCESS read-write
			STATUS current
			DESCRIPTION
				"Allows adjusting the threshold level for the overload detector"
		::= { eap3000p01v1Entry 69 }

		-- 1.3.6.1.4.1.10106.3.101291.1.1.71
		eap3000p01v1SilenceLevel OBJECT-TYPE
			SYNTAX LevelDbfs1
			MAX-ACCESS read-write
			STATUS current
			DESCRIPTION
				"Allows adjusting the threshold level for the silence detector"
		::= { eap3000p01v1Entry 71 }

		-- 1.3.6.1.4.1.10106.3.101291.1.1.73
		eap3000p01v1SilenceTime OBJECT-TYPE
			SYNTAX TimeS2
			MAX-ACCESS read-write
			STATUS current
			DESCRIPTION
				"Allows adjusting the time for the silence detector"
		::= { eap3000p01v1Entry 73 }

		-- 1.3.6.1.4.1.10106.3.101291.1.1.75
		eap3000p01v1NoSig OBJECT-TYPE
			SYNTAX BitFail
			MAX-ACCESS read-only
			STATUS current
			DESCRIPTION
				"SDI input signal status"
		::= { eap3000p01v1Entry 75 }

		-- 1.3.6.1.4.1.10106.3.101291.1.1.76
		eap3000p01v1NoSigTrapEnable OBJECT-TYPE
			SYNTAX AlarmEnable
			MAX-ACCESS read-write
			STATUS current
			DESCRIPTION
				"SDI input signal status Trap Enable"
		::= { eap3000p01v1Entry 76 }

		-- 1.3.6.1.4.1.10106.3.101291.1.1.77
		eap3000p01v1MaxEq OBJECT-TYPE
			SYNTAX BitFail
			MAX-ACCESS read-only
			STATUS current
			DESCRIPTION
				"Indicates maximun equalization"
		::= { eap3000p01v1Entry 77 }

		-- 1.3.6.1.4.1.10106.3.101291.1.1.79
		eap3000p01v1EdhErr OBJECT-TYPE
			SYNTAX BitFail
			MAX-ACCESS read-only
			STATUS current
			DESCRIPTION
				"Indicates EDH errors"
		::= { eap3000p01v1Entry 79 }

		-- 1.3.6.1.4.1.10106.3.101291.1.1.81
		eap3000p01v1PckAGr1 OBJECT-TYPE
			SYNTAX Bit0No1Yes
			MAX-ACCESS read-only
			STATUS current
			DESCRIPTION
				"Group 1 normal audio packets (20 bits) detected"
		::= { eap3000p01v1Entry 81 }

		-- 1.3.6.1.4.1.10106.3.101291.1.1.83
		eap3000p01v1PckAGr2 OBJECT-TYPE
			SYNTAX Bit0No1Yes
			MAX-ACCESS read-only
			STATUS current
			DESCRIPTION
				"Group 2 normal audio packets (20 bits) detected"
		::= { eap3000p01v1Entry 83 }

		-- 1.3.6.1.4.1.10106.3.101291.1.1.85
		eap3000p01v1PckAGr3 OBJECT-TYPE
			SYNTAX Bit0No1Yes
			MAX-ACCESS read-only
			STATUS current
			DESCRIPTION
				"Group 3 normal audio packets (20 bits) detected"
		::= { eap3000p01v1Entry 85 }

		-- 1.3.6.1.4.1.10106.3.101291.1.1.87
		eap3000p01v1PckAGr4 OBJECT-TYPE
			SYNTAX Bit0No1Yes
			MAX-ACCESS read-only
			STATUS current
			DESCRIPTION
				"Group 4 normal audio packets (20 bits) detected"
		::= { eap3000p01v1Entry 87 }

		-- 1.3.6.1.4.1.10106.3.101291.1.1.89
		eap3000p01v1VuLevCh1 OBJECT-TYPE
			SYNTAX LevelDbfs1
			MAX-ACCESS read-only
			STATUS current
			DESCRIPTION
				"Channel 1 VU level"
		::= { eap3000p01v1Entry 89 }

		-- 1.3.6.1.4.1.10106.3.101291.1.1.91
		eap3000p01v1VuLevCh2 OBJECT-TYPE
			SYNTAX LevelDbfs1
			MAX-ACCESS read-only
			STATUS current
			DESCRIPTION
				"Channel 2 VU level"
		::= { eap3000p01v1Entry 91 }

		-- 1.3.6.1.4.1.10106.3.101291.1.1.93
		eap3000p01v1VuLevCh3 OBJECT-TYPE
			SYNTAX LevelDbfs1
			MAX-ACCESS read-only
			STATUS current
			DESCRIPTION
				"Channel 3 VU level"
		::= { eap3000p01v1Entry 93 }

		-- 1.3.6.1.4.1.10106.3.101291.1.1.95
		eap3000p01v1VuLevCh4 OBJECT-TYPE
			SYNTAX LevelDbfs1
			MAX-ACCESS read-only
			STATUS current
			DESCRIPTION
				"Channel 4 VU level"
		::= { eap3000p01v1Entry 95 }

		-- 1.3.6.1.4.1.10106.3.101291.1.1.97
		eap3000p01v1PeakLevCh1 OBJECT-TYPE
			SYNTAX LevelDbfs1
			MAX-ACCESS read-only
			STATUS current
			DESCRIPTION
				"Channel 1 peak level"
		::= { eap3000p01v1Entry 97 }

		-- 1.3.6.1.4.1.10106.3.101291.1.1.99
		eap3000p01v1PeakLevCh2 OBJECT-TYPE
			SYNTAX LevelDbfs1
			MAX-ACCESS read-only
			STATUS current
			DESCRIPTION
				"Channel 2 peak level"
		::= { eap3000p01v1Entry 99 }

		-- 1.3.6.1.4.1.10106.3.101291.1.1.101
		eap3000p01v1PeakLevCh3 OBJECT-TYPE
			SYNTAX LevelDbfs1
			MAX-ACCESS read-only
			STATUS current
			DESCRIPTION
				"Channel 3 peak level"
		::= { eap3000p01v1Entry 101 }

		-- 1.3.6.1.4.1.10106.3.101291.1.1.103
		eap3000p01v1PeakLevCh4 OBJECT-TYPE
			SYNTAX LevelDbfs1
			MAX-ACCESS read-only
			STATUS current
			DESCRIPTION
				"Channel 4 peak level"
		::= { eap3000p01v1Entry 103 }

		-- 1.3.6.1.4.1.10106.3.101291.1.1.105
		eap3000p01v1Antiph12 OBJECT-TYPE
			SYNTAX BitFail
			MAX-ACCESS read-only
			STATUS current
			DESCRIPTION
				"Antiphase fail Ch.1-Ch.2"
		::= { eap3000p01v1Entry 105 }

		-- 1.3.6.1.4.1.10106.3.101291.1.1.106
		eap3000p01v1Antiph12TrapEnable OBJECT-TYPE
			SYNTAX AlarmEnable
			MAX-ACCESS read-write
			STATUS current
			DESCRIPTION
				"Antiphase fail Ch.1-Ch.2 Trap Enable"
		::= { eap3000p01v1Entry 106 }

		-- 1.3.6.1.4.1.10106.3.101291.1.1.107
		eap3000p01v1Antiph34 OBJECT-TYPE
			SYNTAX BitFail
			MAX-ACCESS read-only
			STATUS current
			DESCRIPTION
				"Antiphase fail Ch.3-Ch.4"
		::= { eap3000p01v1Entry 107 }

		-- 1.3.6.1.4.1.10106.3.101291.1.1.108
		eap3000p01v1Antiph34TrapEnable OBJECT-TYPE
			SYNTAX AlarmEnable
			MAX-ACCESS read-write
			STATUS current
			DESCRIPTION
				"Antiphase fail Ch.3-Ch.4 Trap Enable"
		::= { eap3000p01v1Entry 108 }

		-- 1.3.6.1.4.1.10106.3.101291.1.1.109
		eap3000p01v1SilCh1 OBJECT-TYPE
			SYNTAX BitFail
			MAX-ACCESS read-only
			STATUS current
			DESCRIPTION
				"Channel 1 silence"
		::= { eap3000p01v1Entry 109 }

		-- 1.3.6.1.4.1.10106.3.101291.1.1.110
		eap3000p01v1SilCh1TrapEnable OBJECT-TYPE
			SYNTAX AlarmEnable
			MAX-ACCESS read-write
			STATUS current
			DESCRIPTION
				"Channel 1 silence Trap Enable"
		::= { eap3000p01v1Entry 110 }

		-- 1.3.6.1.4.1.10106.3.101291.1.1.111
		eap3000p01v1SilCh2 OBJECT-TYPE
			SYNTAX BitFail
			MAX-ACCESS read-only
			STATUS current
			DESCRIPTION
				"Channel 2 silence"
		::= { eap3000p01v1Entry 111 }

		-- 1.3.6.1.4.1.10106.3.101291.1.1.112
		eap3000p01v1SilCh2TrapEnable OBJECT-TYPE
			SYNTAX AlarmEnable
			MAX-ACCESS read-write
			STATUS current
			DESCRIPTION
				"Channel 2 silence Trap Enable"
		::= { eap3000p01v1Entry 112 }

		-- 1.3.6.1.4.1.10106.3.101291.1.1.113
		eap3000p01v1SilCh3 OBJECT-TYPE
			SYNTAX BitFail
			MAX-ACCESS read-only
			STATUS current
			DESCRIPTION
				"Channel 3 silence"
		::= { eap3000p01v1Entry 113 }

		-- 1.3.6.1.4.1.10106.3.101291.1.1.114
		eap3000p01v1SilCh3TrapEnable OBJECT-TYPE
			SYNTAX AlarmEnable
			MAX-ACCESS read-write
			STATUS current
			DESCRIPTION
				"Channel 3 silence Trap Enable"
		::= { eap3000p01v1Entry 114 }

		-- 1.3.6.1.4.1.10106.3.101291.1.1.115
		eap3000p01v1SilCh4 OBJECT-TYPE
			SYNTAX BitFail
			MAX-ACCESS read-only
			STATUS current
			DESCRIPTION
				"Channel 4 silence"
		::= { eap3000p01v1Entry 115 }

		-- 1.3.6.1.4.1.10106.3.101291.1.1.116
		eap3000p01v1SilCh4TrapEnable OBJECT-TYPE
			SYNTAX AlarmEnable
			MAX-ACCESS read-write
			STATUS current
			DESCRIPTION
				"Channel 4 silence Trap Enable"
		::= { eap3000p01v1Entry 116 }

		-- 1.3.6.1.4.1.10106.3.101291.1.1.117
		eap3000p01v1OvlCh1 OBJECT-TYPE
			SYNTAX BitFail
			MAX-ACCESS read-only
			STATUS current
			DESCRIPTION
				"Channel 1 overload"
		::= { eap3000p01v1Entry 117 }

		-- 1.3.6.1.4.1.10106.3.101291.1.1.118
		eap3000p01v1OvlCh1TrapEnable OBJECT-TYPE
			SYNTAX AlarmEnable
			MAX-ACCESS read-write
			STATUS current
			DESCRIPTION
				"Channel 1 overload Trap Enable"
		::= { eap3000p01v1Entry 118 }

		-- 1.3.6.1.4.1.10106.3.101291.1.1.119
		eap3000p01v1OvlCh2 OBJECT-TYPE
			SYNTAX BitFail
			MAX-ACCESS read-only
			STATUS current
			DESCRIPTION
				"Channel 2 overload"
		::= { eap3000p01v1Entry 119 }

		-- 1.3.6.1.4.1.10106.3.101291.1.1.120
		eap3000p01v1OvlCh2TrapEnable OBJECT-TYPE
			SYNTAX AlarmEnable
			MAX-ACCESS read-write
			STATUS current
			DESCRIPTION
				"Channel 2 overload Trap Enable"
		::= { eap3000p01v1Entry 120 }

		-- 1.3.6.1.4.1.10106.3.101291.1.1.121
		eap3000p01v1OvlCh3 OBJECT-TYPE
			SYNTAX BitFail
			MAX-ACCESS read-only
			STATUS current
			DESCRIPTION
				"Channel 3 overload"
		::= { eap3000p01v1Entry 121 }

		-- 1.3.6.1.4.1.10106.3.101291.1.1.122
		eap3000p01v1OvlCh3TrapEnable OBJECT-TYPE
			SYNTAX AlarmEnable
			MAX-ACCESS read-write
			STATUS current
			DESCRIPTION
				"Channel 3 overload Trap Enable"
		::= { eap3000p01v1Entry 122 }

		-- 1.3.6.1.4.1.10106.3.101291.1.1.123
		eap3000p01v1OvlCh4 OBJECT-TYPE
			SYNTAX BitFail
			MAX-ACCESS read-only
			STATUS current
			DESCRIPTION
				"Channel 4 overload"
		::= { eap3000p01v1Entry 123 }

		-- 1.3.6.1.4.1.10106.3.101291.1.1.124
		eap3000p01v1OvlCh4TrapEnable OBJECT-TYPE
			SYNTAX AlarmEnable
			MAX-ACCESS read-write
			STATUS current
			DESCRIPTION
				"Channel 4 overload Trap Enable"
		::= { eap3000p01v1Entry 124 }

		-- 1.3.6.1.4.1.10106.3.166801
		txe3000p01v1 OBJECT IDENTIFIER ::= { albalaProducts 166801 }

		-- 1.3.6.1.4.1.10106.3.166801.1
		txe3000p01v1Table  OBJECT-TYPE
			SYNTAX SEQUENCE OF Txe3000p01v1Entry
			MAX-ACCESS not-accessible
			STATUS current
			DESCRIPTION
				"Module  TXE3000P01V1 Table"
			::= { txe3000p01v1 1 }

		-- 1.3.6.1.4.1.10106.3.166801.1.1
		txe3000p01v1Entry  OBJECT-TYPE
			SYNTAX Txe3000p01v1Entry
			MAX-ACCESS not-accessible
			STATUS current
			DESCRIPTION
				"Module TXE3000P01V1 Entry"
			INDEX { txe3000p01v1Index }
			::= { txe3000p01v1Table 1 }

			Txe3000p01v1Entry ::=
			SEQUENCE {
				txe3000p01v1Index
				ModuleIndex,
				txe3000p01v1TxBit1
				BitMask,
				txe3000p01v1TxBit2
				BitMask,
				txe3000p01v1TxBit3
				BitMask,
				txe3000p01v1TxtInsLine
				VbiLine,
				txe3000p01v1TxtIns
				Bit0No1Yes,
				txe3000p01v1VitcRdLine
				VbiLine,
				txe3000p01v1VitcRd
				Bit0No1Yes,
				txe3000p01v1NoSignal
				BitFail,
				txe3000p01v1NoSignalTrapEnable
				AlarmEnable,
				txe3000p01v1EdhChk
				BitFail,
				txe3000p01v1VitcOk
				Bit0No1Yes,
				txe3000p01v1Gpi1
				Bit0Off1On,
				txe3000p01v1Gpi2
				Bit0Off1On,
				txe3000p01v1Gpi3
				Bit0Off1On,
				txe3000p01v1Gpi4
				Bit0Off1On,
				txe3000p01v1Bit1
				Bit0Off1On,
				txe3000p01v1Bit2
				Bit0Off1On,
				txe3000p01v1Bit3
				Bit0Off1On,
				txe3000p01v1Bit4
				Bit0Off1On,
				txe3000p01v1VitcHour
				TimeH1,
				txe3000p01v1VitcMin
				TimeM1,
				txe3000p01v1VitcSec
				TimeS1,
				txe3000p01v1VitcFrame
				Frame
			 }

		-- 1.3.6.1.4.1.10106.3.101291.1.1.1
		txe3000p01v1Index OBJECT-TYPE
			SYNTAX ModuleIndex
			MAX-ACCESS read-only
			STATUS current
			DESCRIPTION
				"Index of TXE3000P01V1 Table"
		::= { txe3000p01v1Entry 1 }

		-- 1.3.6.1.4.1.10106.3.101291.1.1.3
		txe3000p01v1TxBit1 OBJECT-TYPE
			SYNTAX BitMask
			MAX-ACCESS read-write
			STATUS current
			DESCRIPTION
				"Bit 1 to be transmitted"
		::= { txe3000p01v1Entry 3 }

		-- 1.3.6.1.4.1.10106.3.101291.1.1.5
		txe3000p01v1TxBit2 OBJECT-TYPE
			SYNTAX BitMask
			MAX-ACCESS read-write
			STATUS current
			DESCRIPTION
				"Bit 2 to be transmitted"
		::= { txe3000p01v1Entry 5 }

		-- 1.3.6.1.4.1.10106.3.101291.1.1.7
		txe3000p01v1TxBit3 OBJECT-TYPE
			SYNTAX BitMask
			MAX-ACCESS read-write
			STATUS current
			DESCRIPTION
				"Bit 3 to be transmitted"
		::= { txe3000p01v1Entry 7 }

		-- 1.3.6.1.4.1.10106.3.101291.1.1.9
		txe3000p01v1TxtInsLine OBJECT-TYPE
			SYNTAX VbiLine
			MAX-ACCESS read-write
			STATUS current
			DESCRIPTION
				"Allows selecting the VBI line in which the teletext information is transmitted"
		::= { txe3000p01v1Entry 9 }

		-- 1.3.6.1.4.1.10106.3.101291.1.1.11
		txe3000p01v1TxtIns OBJECT-TYPE
			SYNTAX Bit0No1Yes
			MAX-ACCESS read-write
			STATUS current
			DESCRIPTION
				"Allows selecting it the teletext information is transmitted"
		::= { txe3000p01v1Entry 11 }

		-- 1.3.6.1.4.1.10106.3.101291.1.1.13
		txe3000p01v1VitcRdLine OBJECT-TYPE
			SYNTAX VbiLine
			MAX-ACCESS read-write
			STATUS current
			DESCRIPTION
				"Allows selecting the VBI line that contains the VITC information"
		::= { txe3000p01v1Entry 13 }

		-- 1.3.6.1.4.1.10106.3.101291.1.1.15
		txe3000p01v1VitcRd OBJECT-TYPE
			SYNTAX Bit0No1Yes
			MAX-ACCESS read-write
			STATUS current
			DESCRIPTION
				"Allows selecting if the VITC information is read to be inserted in the teletext"
		::= { txe3000p01v1Entry 15 }

		-- 1.3.6.1.4.1.10106.3.101291.1.1.17
		txe3000p01v1NoSignal OBJECT-TYPE
			SYNTAX BitFail
			MAX-ACCESS read-only
			STATUS current
			DESCRIPTION
				"SDI input signal status"
		::= { txe3000p01v1Entry 17 }

		-- 1.3.6.1.4.1.10106.3.101291.1.1.18
		txe3000p01v1NoSignalTrapEnable OBJECT-TYPE
			SYNTAX AlarmEnable
			MAX-ACCESS read-write
			STATUS current
			DESCRIPTION
				"SDI input signal status Trap Enable"
		::= { txe3000p01v1Entry 18 }

		-- 1.3.6.1.4.1.10106.3.101291.1.1.19
		txe3000p01v1EdhChk OBJECT-TYPE
			SYNTAX BitFail
			MAX-ACCESS read-only
			STATUS current
			DESCRIPTION
				"The EDH packet has wrong checksum"
		::= { txe3000p01v1Entry 19 }

		-- 1.3.6.1.4.1.10106.3.101291.1.1.21
		txe3000p01v1VitcOk OBJECT-TYPE
			SYNTAX Bit0No1Yes
			MAX-ACCESS read-only
			STATUS current
			DESCRIPTION
				"The VITC data have been correcty decoded"
		::= { txe3000p01v1Entry 21 }

		-- 1.3.6.1.4.1.10106.3.101291.1.1.23
		txe3000p01v1Gpi1 OBJECT-TYPE
			SYNTAX Bit0Off1On
			MAX-ACCESS read-only
			STATUS current
			DESCRIPTION
				"Transmitted GPI1"
		::= { txe3000p01v1Entry 23 }

		-- 1.3.6.1.4.1.10106.3.101291.1.1.25
		txe3000p01v1Gpi2 OBJECT-TYPE
			SYNTAX Bit0Off1On
			MAX-ACCESS read-only
			STATUS current
			DESCRIPTION
				"Transmitted GPI2"
		::= { txe3000p01v1Entry 25 }

		-- 1.3.6.1.4.1.10106.3.101291.1.1.27
		txe3000p01v1Gpi3 OBJECT-TYPE
			SYNTAX Bit0Off1On
			MAX-ACCESS read-only
			STATUS current
			DESCRIPTION
				"Transmitted GPI3"
		::= { txe3000p01v1Entry 27 }

		-- 1.3.6.1.4.1.10106.3.101291.1.1.29
		txe3000p01v1Gpi4 OBJECT-TYPE
			SYNTAX Bit0Off1On
			MAX-ACCESS read-only
			STATUS current
			DESCRIPTION
				"Transmitted GPI4"
		::= { txe3000p01v1Entry 29 }

		-- 1.3.6.1.4.1.10106.3.101291.1.1.31
		txe3000p01v1Bit1 OBJECT-TYPE
			SYNTAX Bit0Off1On
			MAX-ACCESS read-only
			STATUS current
			DESCRIPTION
				"Transmitted BIT1"
		::= { txe3000p01v1Entry 31 }

		-- 1.3.6.1.4.1.10106.3.101291.1.1.33
		txe3000p01v1Bit2 OBJECT-TYPE
			SYNTAX Bit0Off1On
			MAX-ACCESS read-only
			STATUS current
			DESCRIPTION
				"Transmitted BIT2"
		::= { txe3000p01v1Entry 33 }

		-- 1.3.6.1.4.1.10106.3.101291.1.1.35
		txe3000p01v1Bit3 OBJECT-TYPE
			SYNTAX Bit0Off1On
			MAX-ACCESS read-only
			STATUS current
			DESCRIPTION
				"Transmitted BIT3"
		::= { txe3000p01v1Entry 35 }

		-- 1.3.6.1.4.1.10106.3.101291.1.1.37
		txe3000p01v1Bit4 OBJECT-TYPE
			SYNTAX Bit0Off1On
			MAX-ACCESS read-only
			STATUS current
			DESCRIPTION
				"Transmitted BIT4"
		::= { txe3000p01v1Entry 37 }

		-- 1.3.6.1.4.1.10106.3.101291.1.1.39
		txe3000p01v1VitcHour OBJECT-TYPE
			SYNTAX TimeH1
			MAX-ACCESS read-only
			STATUS current
			DESCRIPTION
				"Hour read from VITC"
		::= { txe3000p01v1Entry 39 }

		-- 1.3.6.1.4.1.10106.3.101291.1.1.41
		txe3000p01v1VitcMin OBJECT-TYPE
			SYNTAX TimeM1
			MAX-ACCESS read-only
			STATUS current
			DESCRIPTION
				"Minute read from VITC"
		::= { txe3000p01v1Entry 41 }

		-- 1.3.6.1.4.1.10106.3.101291.1.1.43
		txe3000p01v1VitcSec OBJECT-TYPE
			SYNTAX TimeS1
			MAX-ACCESS read-only
			STATUS current
			DESCRIPTION
				"Second read from VITC"
		::= { txe3000p01v1Entry 43 }

		-- 1.3.6.1.4.1.10106.3.101291.1.1.45
		txe3000p01v1VitcFrame OBJECT-TYPE
			SYNTAX Frame
			MAX-ACCESS read-only
			STATUS current
			DESCRIPTION
				"Frame read from VITC"
		::= { txe3000p01v1Entry 45 }

		-- 1.3.6.1.4.1.10106.3.166802
		txe3000p01v2 OBJECT IDENTIFIER ::= { albalaProducts 166802 }

		-- 1.3.6.1.4.1.10106.3.166802.1
		txe3000p01v2Table  OBJECT-TYPE
			SYNTAX SEQUENCE OF Txe3000p01v2Entry
			MAX-ACCESS not-accessible
			STATUS current
			DESCRIPTION
				"Module  TXE3000P01V2 Table"
			::= { txe3000p01v2 1 }

		-- 1.3.6.1.4.1.10106.3.166802.1.1
		txe3000p01v2Entry  OBJECT-TYPE
			SYNTAX Txe3000p01v2Entry
			MAX-ACCESS not-accessible
			STATUS current
			DESCRIPTION
				"Module TXE3000P01V2 Entry"
			INDEX { txe3000p01v2Index }
			::= { txe3000p01v2Table 1 }

			Txe3000p01v2Entry ::=
			SEQUENCE {
				txe3000p01v2Index
				ModuleIndex,
				txe3000p01v2TxBit1
				BitMask,
				txe3000p01v2TxBit2
				BitMask,
				txe3000p01v2TxBit3
				BitMask,
				txe3000p01v2TxBit4
				BitMask,
				txe3000p01v2TxtInsLine
				VbiLine,
				txe3000p01v2TxtIns
				Bit0No1Yes,
				txe3000p01v2VitcRdLine
				VbiLine,
				txe3000p01v2VitcRd
				Bit0No1Yes,
				txe3000p01v2NoSignal
				BitFail,
				txe3000p01v2NoSignalTrapEnable
				AlarmEnable,
				txe3000p01v2EdhChk
				BitFail,
				txe3000p01v2VitcOk
				Bit0No1Yes,
				txe3000p01v2Gpi1
				Bit0Off1On,
				txe3000p01v2Gpi2
				Bit0Off1On,
				txe3000p01v2Gpi3
				Bit0Off1On,
				txe3000p01v2Gpi4
				Bit0Off1On,
				txe3000p01v2Bit1
				Bit0Off1On,
				txe3000p01v2Bit2
				Bit0Off1On,
				txe3000p01v2Bit3
				Bit0Off1On,
				txe3000p01v2Bit4
				Bit0Off1On,
				txe3000p01v2VitcHour
				TimeH1,
				txe3000p01v2VitcMin
				TimeM1,
				txe3000p01v2VitcSec
				TimeS1,
				txe3000p01v2VitcFrame
				Frame
			 }

		-- 1.3.6.1.4.1.10106.3.101291.1.1.1
		txe3000p01v2Index OBJECT-TYPE
			SYNTAX ModuleIndex
			MAX-ACCESS read-only
			STATUS current
			DESCRIPTION
				"Index of TXE3000P01V2 Table"
		::= { txe3000p01v2Entry 1 }

		-- 1.3.6.1.4.1.10106.3.101291.1.1.3
		txe3000p01v2TxBit1 OBJECT-TYPE
			SYNTAX BitMask
			MAX-ACCESS read-write
			STATUS current
			DESCRIPTION
				"Bit 1 to be transmitted"
		::= { txe3000p01v2Entry 3 }

		-- 1.3.6.1.4.1.10106.3.101291.1.1.5
		txe3000p01v2TxBit2 OBJECT-TYPE
			SYNTAX BitMask
			MAX-ACCESS read-write
			STATUS current
			DESCRIPTION
				"Bit 2 to be transmitted"
		::= { txe3000p01v2Entry 5 }

		-- 1.3.6.1.4.1.10106.3.101291.1.1.7
		txe3000p01v2TxBit3 OBJECT-TYPE
			SYNTAX BitMask
			MAX-ACCESS read-write
			STATUS current
			DESCRIPTION
				"Bit 3 to be transmitted"
		::= { txe3000p01v2Entry 7 }

		-- 1.3.6.1.4.1.10106.3.101291.1.1.9
		txe3000p01v2TxBit4 OBJECT-TYPE
			SYNTAX BitMask
			MAX-ACCESS read-write
			STATUS current
			DESCRIPTION
				"Bit 4 to be transmitted"
		::= { txe3000p01v2Entry 9 }

		-- 1.3.6.1.4.1.10106.3.101291.1.1.11
		txe3000p01v2TxtInsLine OBJECT-TYPE
			SYNTAX VbiLine
			MAX-ACCESS read-write
			STATUS current
			DESCRIPTION
				"Allows selecting the VBI line in which the teletext information is transmitted"
		::= { txe3000p01v2Entry 11 }

		-- 1.3.6.1.4.1.10106.3.101291.1.1.13
		txe3000p01v2TxtIns OBJECT-TYPE
			SYNTAX Bit0No1Yes
			MAX-ACCESS read-write
			STATUS current
			DESCRIPTION
				"Allows selecting it the teletext information is transmitted"
		::= { txe3000p01v2Entry 13 }

		-- 1.3.6.1.4.1.10106.3.101291.1.1.15
		txe3000p01v2VitcRdLine OBJECT-TYPE
			SYNTAX VbiLine
			MAX-ACCESS read-write
			STATUS current
			DESCRIPTION
				"Allows selecting the VBI line that contains the VITC information"
		::= { txe3000p01v2Entry 15 }

		-- 1.3.6.1.4.1.10106.3.101291.1.1.17
		txe3000p01v2VitcRd OBJECT-TYPE
			SYNTAX Bit0No1Yes
			MAX-ACCESS read-write
			STATUS current
			DESCRIPTION
				"Allows selecting if the VITC information is read to be inserted in the teletext"
		::= { txe3000p01v2Entry 17 }

		-- 1.3.6.1.4.1.10106.3.101291.1.1.19
		txe3000p01v2NoSignal OBJECT-TYPE
			SYNTAX BitFail
			MAX-ACCESS read-only
			STATUS current
			DESCRIPTION
				"SDI input signal status"
		::= { txe3000p01v2Entry 19 }

		-- 1.3.6.1.4.1.10106.3.101291.1.1.20
		txe3000p01v2NoSignalTrapEnable OBJECT-TYPE
			SYNTAX AlarmEnable
			MAX-ACCESS read-write
			STATUS current
			DESCRIPTION
				"SDI input signal status Trap Enable"
		::= { txe3000p01v2Entry 20 }

		-- 1.3.6.1.4.1.10106.3.101291.1.1.21
		txe3000p01v2EdhChk OBJECT-TYPE
			SYNTAX BitFail
			MAX-ACCESS read-only
			STATUS current
			DESCRIPTION
				"The EDH packet has wrong checksum"
		::= { txe3000p01v2Entry 21 }

		-- 1.3.6.1.4.1.10106.3.101291.1.1.23
		txe3000p01v2VitcOk OBJECT-TYPE
			SYNTAX Bit0No1Yes
			MAX-ACCESS read-only
			STATUS current
			DESCRIPTION
				"The VITC data have been correcty decoded"
		::= { txe3000p01v2Entry 23 }

		-- 1.3.6.1.4.1.10106.3.101291.1.1.25
		txe3000p01v2Gpi1 OBJECT-TYPE
			SYNTAX Bit0Off1On
			MAX-ACCESS read-only
			STATUS current
			DESCRIPTION
				"Transmitted GPI1"
		::= { txe3000p01v2Entry 25 }

		-- 1.3.6.1.4.1.10106.3.101291.1.1.27
		txe3000p01v2Gpi2 OBJECT-TYPE
			SYNTAX Bit0Off1On
			MAX-ACCESS read-only
			STATUS current
			DESCRIPTION
				"Transmitted GPI2"
		::= { txe3000p01v2Entry 27 }

		-- 1.3.6.1.4.1.10106.3.101291.1.1.29
		txe3000p01v2Gpi3 OBJECT-TYPE
			SYNTAX Bit0Off1On
			MAX-ACCESS read-only
			STATUS current
			DESCRIPTION
				"Transmitted GPI3"
		::= { txe3000p01v2Entry 29 }

		-- 1.3.6.1.4.1.10106.3.101291.1.1.31
		txe3000p01v2Gpi4 OBJECT-TYPE
			SYNTAX Bit0Off1On
			MAX-ACCESS read-only
			STATUS current
			DESCRIPTION
				"Transmitted GPI4"
		::= { txe3000p01v2Entry 31 }

		-- 1.3.6.1.4.1.10106.3.101291.1.1.33
		txe3000p01v2Bit1 OBJECT-TYPE
			SYNTAX Bit0Off1On
			MAX-ACCESS read-only
			STATUS current
			DESCRIPTION
				"Transmitted BIT1"
		::= { txe3000p01v2Entry 33 }

		-- 1.3.6.1.4.1.10106.3.101291.1.1.35
		txe3000p01v2Bit2 OBJECT-TYPE
			SYNTAX Bit0Off1On
			MAX-ACCESS read-only
			STATUS current
			DESCRIPTION
				"Transmitted BIT2"
		::= { txe3000p01v2Entry 35 }

		-- 1.3.6.1.4.1.10106.3.101291.1.1.37
		txe3000p01v2Bit3 OBJECT-TYPE
			SYNTAX Bit0Off1On
			MAX-ACCESS read-only
			STATUS current
			DESCRIPTION
				"Transmitted BIT3"
		::= { txe3000p01v2Entry 37 }

		-- 1.3.6.1.4.1.10106.3.101291.1.1.39
		txe3000p01v2Bit4 OBJECT-TYPE
			SYNTAX Bit0Off1On
			MAX-ACCESS read-only
			STATUS current
			DESCRIPTION
				"Transmitted BIT4"
		::= { txe3000p01v2Entry 39 }

		-- 1.3.6.1.4.1.10106.3.101291.1.1.41
		txe3000p01v2VitcHour OBJECT-TYPE
			SYNTAX TimeH1
			MAX-ACCESS read-only
			STATUS current
			DESCRIPTION
				"Hour read from VITC"
		::= { txe3000p01v2Entry 41 }

		-- 1.3.6.1.4.1.10106.3.101291.1.1.43
		txe3000p01v2VitcMin OBJECT-TYPE
			SYNTAX TimeM1
			MAX-ACCESS read-only
			STATUS current
			DESCRIPTION
				"Minute read from VITC"
		::= { txe3000p01v2Entry 43 }

		-- 1.3.6.1.4.1.10106.3.101291.1.1.45
		txe3000p01v2VitcSec OBJECT-TYPE
			SYNTAX TimeS1
			MAX-ACCESS read-only
			STATUS current
			DESCRIPTION
				"Second read from VITC"
		::= { txe3000p01v2Entry 45 }

		-- 1.3.6.1.4.1.10106.3.101291.1.1.47
		txe3000p01v2VitcFrame OBJECT-TYPE
			SYNTAX Frame
			MAX-ACCESS read-only
			STATUS current
			DESCRIPTION
				"Frame read from VITC"
		::= { txe3000p01v2Entry 47 }

		-- 1.3.6.1.4.1.10106.3.166901
		txd3000p01v1 OBJECT IDENTIFIER ::= { albalaProducts 166901 }

		-- 1.3.6.1.4.1.10106.3.166901.1
		txd3000p01v1Table  OBJECT-TYPE
			SYNTAX SEQUENCE OF Txd3000p01v1Entry
			MAX-ACCESS not-accessible
			STATUS current
			DESCRIPTION
				"Module  TXD3000P01V1 Table"
			::= { txd3000p01v1 1 }

		-- 1.3.6.1.4.1.10106.3.166901.1.1
		txd3000p01v1Entry  OBJECT-TYPE
			SYNTAX Txd3000p01v1Entry
			MAX-ACCESS not-accessible
			STATUS current
			DESCRIPTION
				"Module TXD3000P01V1 Entry"
			INDEX { txd3000p01v1Index }
			::= { txd3000p01v1Table 1 }

			Txd3000p01v1Entry ::=
			SEQUENCE {
				txd3000p01v1Index
				ModuleIndex,
				txd3000p01v1GpoBit1
				Bit0Gpi1Bit,
				txd3000p01v1GpoBit2
				Bit0Gpi1Bit,
				txd3000p01v1GpoBit3
				Bit0Gpi1Bit,
				txd3000p01v1GpoBit4
				Bit0Gpi1Bit,
				txd3000p01v1TxtRdLine
				VbiLine,
				txd3000p01v1TxtClr
				Bit0No1Yes,
				txd3000p01v1TxtRd
				Bit0No1Yes,
				txd3000p01v1VitcInsLine
				VbiLine,
				txd3000p01v1VitcIns
				Bit0No1Yes,
				txd3000p01v1NoSignal
				BitFail,
				txd3000p01v1NoSignalTrapEnable
				AlarmEnable,
				txd3000p01v1TxtOk
				Bit0No1Yes,
				txd3000p01v1Gpi1
				Bit0Off1On,
				txd3000p01v1Gpi2
				Bit0Off1On,
				txd3000p01v1Gpi3
				Bit0Off1On,
				txd3000p01v1Gpi4
				Bit0Off1On,
				txd3000p01v1Bit1
				Bit0Off1On,
				txd3000p01v1Bit2
				Bit0Off1On,
				txd3000p01v1Bit3
				Bit0Off1On,
				txd3000p01v1Bit4
				Bit0Off1On,
				txd3000p01v1VitcHour
				TimeH1,
				txd3000p01v1VitcMin
				TimeM1,
				txd3000p01v1VitcSec
				TimeS1,
				txd3000p01v1VitcFrame
				Frame
			 }

		-- 1.3.6.1.4.1.10106.3.101291.1.1.1
		txd3000p01v1Index OBJECT-TYPE
			SYNTAX ModuleIndex
			MAX-ACCESS read-only
			STATUS current
			DESCRIPTION
				"Index of TXD3000P01V1 Table"
		::= { txd3000p01v1Entry 1 }

		-- 1.3.6.1.4.1.10106.3.101291.1.1.3
		txd3000p01v1GpoBit1 OBJECT-TYPE
			SYNTAX Bit0Gpi1Bit
			MAX-ACCESS read-write
			STATUS current
			DESCRIPTION
				"Allows selecting if the GPO1 is controlled by the TXE GPI1 or by the TXE BIT1"
		::= { txd3000p01v1Entry 3 }

		-- 1.3.6.1.4.1.10106.3.101291.1.1.5
		txd3000p01v1GpoBit2 OBJECT-TYPE
			SYNTAX Bit0Gpi1Bit
			MAX-ACCESS read-write
			STATUS current
			DESCRIPTION
				"Allows selecting if the GPO2 is controlled by the TXE GPI2 or by the TXE BIT2"
		::= { txd3000p01v1Entry 5 }

		-- 1.3.6.1.4.1.10106.3.101291.1.1.7
		txd3000p01v1GpoBit3 OBJECT-TYPE
			SYNTAX Bit0Gpi1Bit
			MAX-ACCESS read-write
			STATUS current
			DESCRIPTION
				"Allows selecting if the GPO3 is controlled by the TXE GPI3 or by the TXE BIT3"
		::= { txd3000p01v1Entry 7 }

		-- 1.3.6.1.4.1.10106.3.101291.1.1.9
		txd3000p01v1GpoBit4 OBJECT-TYPE
			SYNTAX Bit0Gpi1Bit
			MAX-ACCESS read-write
			STATUS current
			DESCRIPTION
				"Allows selecting if the GPO4 is controlled by the TXE GPI4 or by the TXE BIT4"
		::= { txd3000p01v1Entry 9 }

		-- 1.3.6.1.4.1.10106.3.101291.1.1.11
		txd3000p01v1TxtRdLine OBJECT-TYPE
			SYNTAX VbiLine
			MAX-ACCESS read-write
			STATUS current
			DESCRIPTION
				"Allows selecting the VBI line that contains the teletext information"
		::= { txd3000p01v1Entry 11 }

		-- 1.3.6.1.4.1.10106.3.101291.1.1.13
		txd3000p01v1TxtClr OBJECT-TYPE
			SYNTAX Bit0No1Yes
			MAX-ACCESS read-write
			STATUS current
			DESCRIPTION
				"Allows selecting if the reserved teletext line is deleted"
		::= { txd3000p01v1Entry 13 }

		-- 1.3.6.1.4.1.10106.3.101291.1.1.15
		txd3000p01v1TxtRd OBJECT-TYPE
			SYNTAX Bit0No1Yes
			MAX-ACCESS read-write
			STATUS current
			DESCRIPTION
				"Allows selecting if the teletext information is read"
		::= { txd3000p01v1Entry 15 }

		-- 1.3.6.1.4.1.10106.3.101291.1.1.17
		txd3000p01v1VitcInsLine OBJECT-TYPE
			SYNTAX VbiLine
			MAX-ACCESS read-write
			STATUS current
			DESCRIPTION
				"Allows selecting the VBI line in which the VITC information is inserted"
		::= { txd3000p01v1Entry 17 }

		-- 1.3.6.1.4.1.10106.3.101291.1.1.19
		txd3000p01v1VitcIns OBJECT-TYPE
			SYNTAX Bit0No1Yes
			MAX-ACCESS read-write
			STATUS current
			DESCRIPTION
				"Allows selecting it the VITC information is inserted"
		::= { txd3000p01v1Entry 19 }

		-- 1.3.6.1.4.1.10106.3.101291.1.1.21
		txd3000p01v1NoSignal OBJECT-TYPE
			SYNTAX BitFail
			MAX-ACCESS read-only
			STATUS current
			DESCRIPTION
				"SDI input signal status"
		::= { txd3000p01v1Entry 21 }

		-- 1.3.6.1.4.1.10106.3.101291.1.1.22
		txd3000p01v1NoSignalTrapEnable OBJECT-TYPE
			SYNTAX AlarmEnable
			MAX-ACCESS read-write
			STATUS current
			DESCRIPTION
				"SDI input signal status Trap Enable"
		::= { txd3000p01v1Entry 22 }

		-- 1.3.6.1.4.1.10106.3.101291.1.1.23
		txd3000p01v1TxtOk OBJECT-TYPE
			SYNTAX Bit0No1Yes
			MAX-ACCESS read-only
			STATUS current
			DESCRIPTION
				"The TXT data have been correcty decoded"
		::= { txd3000p01v1Entry 23 }

		-- 1.3.6.1.4.1.10106.3.101291.1.1.25
		txd3000p01v1Gpi1 OBJECT-TYPE
			SYNTAX Bit0Off1On
			MAX-ACCESS read-only
			STATUS current
			DESCRIPTION
				"Transmitted GPI1"
		::= { txd3000p01v1Entry 25 }

		-- 1.3.6.1.4.1.10106.3.101291.1.1.27
		txd3000p01v1Gpi2 OBJECT-TYPE
			SYNTAX Bit0Off1On
			MAX-ACCESS read-only
			STATUS current
			DESCRIPTION
				"Transmitted GPI2"
		::= { txd3000p01v1Entry 27 }

		-- 1.3.6.1.4.1.10106.3.101291.1.1.29
		txd3000p01v1Gpi3 OBJECT-TYPE
			SYNTAX Bit0Off1On
			MAX-ACCESS read-only
			STATUS current
			DESCRIPTION
				"Transmitted GPI3"
		::= { txd3000p01v1Entry 29 }

		-- 1.3.6.1.4.1.10106.3.101291.1.1.31
		txd3000p01v1Gpi4 OBJECT-TYPE
			SYNTAX Bit0Off1On
			MAX-ACCESS read-only
			STATUS current
			DESCRIPTION
				"Transmitted GPI4"
		::= { txd3000p01v1Entry 31 }

		-- 1.3.6.1.4.1.10106.3.101291.1.1.33
		txd3000p01v1Bit1 OBJECT-TYPE
			SYNTAX Bit0Off1On
			MAX-ACCESS read-only
			STATUS current
			DESCRIPTION
				"Transmitted BIT1"
		::= { txd3000p01v1Entry 33 }

		-- 1.3.6.1.4.1.10106.3.101291.1.1.35
		txd3000p01v1Bit2 OBJECT-TYPE
			SYNTAX Bit0Off1On
			MAX-ACCESS read-only
			STATUS current
			DESCRIPTION
				"Transmitted BIT2"
		::= { txd3000p01v1Entry 35 }

		-- 1.3.6.1.4.1.10106.3.101291.1.1.37
		txd3000p01v1Bit3 OBJECT-TYPE
			SYNTAX Bit0Off1On
			MAX-ACCESS read-only
			STATUS current
			DESCRIPTION
				"Transmitted BIT3"
		::= { txd3000p01v1Entry 37 }

		-- 1.3.6.1.4.1.10106.3.101291.1.1.39
		txd3000p01v1Bit4 OBJECT-TYPE
			SYNTAX Bit0Off1On
			MAX-ACCESS read-only
			STATUS current
			DESCRIPTION
				"Transmitted BIT4"
		::= { txd3000p01v1Entry 39 }

		-- 1.3.6.1.4.1.10106.3.101291.1.1.41
		txd3000p01v1VitcHour OBJECT-TYPE
			SYNTAX TimeH1
			MAX-ACCESS read-only
			STATUS current
			DESCRIPTION
				"Hour read from VITC"
		::= { txd3000p01v1Entry 41 }

		-- 1.3.6.1.4.1.10106.3.101291.1.1.43
		txd3000p01v1VitcMin OBJECT-TYPE
			SYNTAX TimeM1
			MAX-ACCESS read-only
			STATUS current
			DESCRIPTION
				"Minute read from VITC"
		::= { txd3000p01v1Entry 43 }

		-- 1.3.6.1.4.1.10106.3.101291.1.1.45
		txd3000p01v1VitcSec OBJECT-TYPE
			SYNTAX TimeS1
			MAX-ACCESS read-only
			STATUS current
			DESCRIPTION
				"Second read from VITC"
		::= { txd3000p01v1Entry 45 }

		-- 1.3.6.1.4.1.10106.3.101291.1.1.47
		txd3000p01v1VitcFrame OBJECT-TYPE
			SYNTAX Frame
			MAX-ACCESS read-only
			STATUS current
			DESCRIPTION
				"Frame read from VITC"
		::= { txd3000p01v1Entry 47 }

		-- 1.3.6.1.4.1.10106.3.166902
		txd3000p01v2 OBJECT IDENTIFIER ::= { albalaProducts 166902 }

		-- 1.3.6.1.4.1.10106.3.166902.1
		txd3000p01v2Table  OBJECT-TYPE
			SYNTAX SEQUENCE OF Txd3000p01v2Entry
			MAX-ACCESS not-accessible
			STATUS current
			DESCRIPTION
				"Module  TXD3000P01V2 Table"
			::= { txd3000p01v2 1 }

		-- 1.3.6.1.4.1.10106.3.166902.1.1
		txd3000p01v2Entry  OBJECT-TYPE
			SYNTAX Txd3000p01v2Entry
			MAX-ACCESS not-accessible
			STATUS current
			DESCRIPTION
				"Module TXD3000P01V2 Entry"
			INDEX { txd3000p01v2Index }
			::= { txd3000p01v2Table 1 }

			Txd3000p01v2Entry ::=
			SEQUENCE {
				txd3000p01v2Index
				ModuleIndex,
				txd3000p01v2TxtRdLine
				VbiLine,
				txd3000p01v2TxtClr
				Bit0No1Yes,
				txd3000p01v2TxtRd
				Bit0No1Yes,
				txd3000p01v2VitcInsLine
				VbiLine,
				txd3000p01v2VitcIns
				Bit0No1Yes,
				txd3000p01v2GpoBit1
				SelBit2,
				txd3000p01v2GpoBit2
				SelBit2,
				txd3000p01v2GpoBit3
				SelBit2,
				txd3000p01v2GpoBit4
				SelBit2,
				txd3000p01v2NoSignal
				BitFail,
				txd3000p01v2NoSignalTrapEnable
				AlarmEnable,
				txd3000p01v2TxtOk
				Bit0No1Yes,
				txd3000p01v2Gpi1
				Bit0Off1On,
				txd3000p01v2Gpi2
				Bit0Off1On,
				txd3000p01v2Gpi3
				Bit0Off1On,
				txd3000p01v2Gpi4
				Bit0Off1On,
				txd3000p01v2Bit1
				Bit0Off1On,
				txd3000p01v2Bit2
				Bit0Off1On,
				txd3000p01v2Bit3
				Bit0Off1On,
				txd3000p01v2Bit4
				Bit0Off1On,
				txd3000p01v2VitcHour
				TimeH1,
				txd3000p01v2VitcMin
				TimeM1,
				txd3000p01v2VitcSec
				TimeS1,
				txd3000p01v2VitcFrame
				Frame
			 }

		-- 1.3.6.1.4.1.10106.3.101291.1.1.1
		txd3000p01v2Index OBJECT-TYPE
			SYNTAX ModuleIndex
			MAX-ACCESS read-only
			STATUS current
			DESCRIPTION
				"Index of TXD3000P01V2 Table"
		::= { txd3000p01v2Entry 1 }

		-- 1.3.6.1.4.1.10106.3.101291.1.1.3
		txd3000p01v2TxtRdLine OBJECT-TYPE
			SYNTAX VbiLine
			MAX-ACCESS read-write
			STATUS current
			DESCRIPTION
				"Allows selecting the VBI line that contains the teletext information"
		::= { txd3000p01v2Entry 3 }

		-- 1.3.6.1.4.1.10106.3.101291.1.1.5
		txd3000p01v2TxtClr OBJECT-TYPE
			SYNTAX Bit0No1Yes
			MAX-ACCESS read-write
			STATUS current
			DESCRIPTION
				"Allows selecting if the reserved teletext line is deleted"
		::= { txd3000p01v2Entry 5 }

		-- 1.3.6.1.4.1.10106.3.101291.1.1.7
		txd3000p01v2TxtRd OBJECT-TYPE
			SYNTAX Bit0No1Yes
			MAX-ACCESS read-write
			STATUS current
			DESCRIPTION
				"Allows selecting if the teletext information is read"
		::= { txd3000p01v2Entry 7 }

		-- 1.3.6.1.4.1.10106.3.101291.1.1.9
		txd3000p01v2VitcInsLine OBJECT-TYPE
			SYNTAX VbiLine
			MAX-ACCESS read-write
			STATUS current
			DESCRIPTION
				"Allows selecting the VBI line in which the VITC information is inserted"
		::= { txd3000p01v2Entry 9 }

		-- 1.3.6.1.4.1.10106.3.101291.1.1.11
		txd3000p01v2VitcIns OBJECT-TYPE
			SYNTAX Bit0No1Yes
			MAX-ACCESS read-write
			STATUS current
			DESCRIPTION
				"Allows selecting it the VITC information is inserted"
		::= { txd3000p01v2Entry 11 }

		-- 1.3.6.1.4.1.10106.3.101291.1.1.13
		txd3000p01v2GpoBit1 OBJECT-TYPE
			SYNTAX SelBit2
			MAX-ACCESS read-write
			STATUS current
			DESCRIPTION
				"Allows selecting if the GPO1 is controlled by the TXE GPI1 or by the TXE BIT1"
		::= { txd3000p01v2Entry 13 }

		-- 1.3.6.1.4.1.10106.3.101291.1.1.15
		txd3000p01v2GpoBit2 OBJECT-TYPE
			SYNTAX SelBit2
			MAX-ACCESS read-write
			STATUS current
			DESCRIPTION
				"Allows selecting if the GPO2 is controlled by the TXE GPI2 or by the TXE BIT2"
		::= { txd3000p01v2Entry 15 }

		-- 1.3.6.1.4.1.10106.3.101291.1.1.17
		txd3000p01v2GpoBit3 OBJECT-TYPE
			SYNTAX SelBit2
			MAX-ACCESS read-write
			STATUS current
			DESCRIPTION
				"Allows selecting if the GPO3 is controlled by the TXE GPI3 or by the TXE BIT3"
		::= { txd3000p01v2Entry 17 }

		-- 1.3.6.1.4.1.10106.3.101291.1.1.19
		txd3000p01v2GpoBit4 OBJECT-TYPE
			SYNTAX SelBit2
			MAX-ACCESS read-write
			STATUS current
			DESCRIPTION
				"Allows selecting if the GPO4 is controlled by the TXE GPI4 or by the TXE BIT4"
		::= { txd3000p01v2Entry 19 }

		-- 1.3.6.1.4.1.10106.3.101291.1.1.21
		txd3000p01v2NoSignal OBJECT-TYPE
			SYNTAX BitFail
			MAX-ACCESS read-only
			STATUS current
			DESCRIPTION
				"SDI input signal status"
		::= { txd3000p01v2Entry 21 }

		-- 1.3.6.1.4.1.10106.3.101291.1.1.22
		txd3000p01v2NoSignalTrapEnable OBJECT-TYPE
			SYNTAX AlarmEnable
			MAX-ACCESS read-write
			STATUS current
			DESCRIPTION
				"SDI input signal status Trap Enable"
		::= { txd3000p01v2Entry 22 }

		-- 1.3.6.1.4.1.10106.3.101291.1.1.23
		txd3000p01v2TxtOk OBJECT-TYPE
			SYNTAX Bit0No1Yes
			MAX-ACCESS read-only
			STATUS current
			DESCRIPTION
				"The TXT data have been correcty decoded"
		::= { txd3000p01v2Entry 23 }

		-- 1.3.6.1.4.1.10106.3.101291.1.1.25
		txd3000p01v2Gpi1 OBJECT-TYPE
			SYNTAX Bit0Off1On
			MAX-ACCESS read-only
			STATUS current
			DESCRIPTION
				"Transmitted GPI1"
		::= { txd3000p01v2Entry 25 }

		-- 1.3.6.1.4.1.10106.3.101291.1.1.27
		txd3000p01v2Gpi2 OBJECT-TYPE
			SYNTAX Bit0Off1On
			MAX-ACCESS read-only
			STATUS current
			DESCRIPTION
				"Transmitted GPI2"
		::= { txd3000p01v2Entry 27 }

		-- 1.3.6.1.4.1.10106.3.101291.1.1.29
		txd3000p01v2Gpi3 OBJECT-TYPE
			SYNTAX Bit0Off1On
			MAX-ACCESS read-only
			STATUS current
			DESCRIPTION
				"Transmitted GPI3"
		::= { txd3000p01v2Entry 29 }

		-- 1.3.6.1.4.1.10106.3.101291.1.1.31
		txd3000p01v2Gpi4 OBJECT-TYPE
			SYNTAX Bit0Off1On
			MAX-ACCESS read-only
			STATUS current
			DESCRIPTION
				"Transmitted GPI4"
		::= { txd3000p01v2Entry 31 }

		-- 1.3.6.1.4.1.10106.3.101291.1.1.33
		txd3000p01v2Bit1 OBJECT-TYPE
			SYNTAX Bit0Off1On
			MAX-ACCESS read-only
			STATUS current
			DESCRIPTION
				"Transmitted BIT1"
		::= { txd3000p01v2Entry 33 }

		-- 1.3.6.1.4.1.10106.3.101291.1.1.35
		txd3000p01v2Bit2 OBJECT-TYPE
			SYNTAX Bit0Off1On
			MAX-ACCESS read-only
			STATUS current
			DESCRIPTION
				"Transmitted BIT2"
		::= { txd3000p01v2Entry 35 }

		-- 1.3.6.1.4.1.10106.3.101291.1.1.37
		txd3000p01v2Bit3 OBJECT-TYPE
			SYNTAX Bit0Off1On
			MAX-ACCESS read-only
			STATUS current
			DESCRIPTION
				"Transmitted BIT3"
		::= { txd3000p01v2Entry 37 }

		-- 1.3.6.1.4.1.10106.3.101291.1.1.39
		txd3000p01v2Bit4 OBJECT-TYPE
			SYNTAX Bit0Off1On
			MAX-ACCESS read-only
			STATUS current
			DESCRIPTION
				"Transmitted BIT4"
		::= { txd3000p01v2Entry 39 }

		-- 1.3.6.1.4.1.10106.3.101291.1.1.41
		txd3000p01v2VitcHour OBJECT-TYPE
			SYNTAX TimeH1
			MAX-ACCESS read-only
			STATUS current
			DESCRIPTION
				"Hour read from VITC"
		::= { txd3000p01v2Entry 41 }

		-- 1.3.6.1.4.1.10106.3.101291.1.1.43
		txd3000p01v2VitcMin OBJECT-TYPE
			SYNTAX TimeM1
			MAX-ACCESS read-only
			STATUS current
			DESCRIPTION
				"Minute read from VITC"
		::= { txd3000p01v2Entry 43 }

		-- 1.3.6.1.4.1.10106.3.101291.1.1.45
		txd3000p01v2VitcSec OBJECT-TYPE
			SYNTAX TimeS1
			MAX-ACCESS read-only
			STATUS current
			DESCRIPTION
				"Second read from VITC"
		::= { txd3000p01v2Entry 45 }

		-- 1.3.6.1.4.1.10106.3.101291.1.1.47
		txd3000p01v2VitcFrame OBJECT-TYPE
			SYNTAX Frame
			MAX-ACCESS read-only
			STATUS current
			DESCRIPTION
				"Frame read from VITC"
		::= { txd3000p01v2Entry 47 }

		-- 1.3.6.1.4.1.10106.3.167201
		vfd3000c01v1 OBJECT IDENTIFIER ::= { albalaProducts 167201 }

		-- 1.3.6.1.4.1.10106.3.167201.1
		vfd3000c01v1Table  OBJECT-TYPE
			SYNTAX SEQUENCE OF Vfd3000c01v1Entry
			MAX-ACCESS not-accessible
			STATUS current
			DESCRIPTION
				"Module  VFD3000C01V1 Table"
			::= { vfd3000c01v1 1 }

		-- 1.3.6.1.4.1.10106.3.167201.1.1
		vfd3000c01v1Entry  OBJECT-TYPE
			SYNTAX Vfd3000c01v1Entry
			MAX-ACCESS not-accessible
			STATUS current
			DESCRIPTION
				"Module VFD3000C01V1 Entry"
			INDEX { vfd3000c01v1Index }
			::= { vfd3000c01v1Table 1 }

			Vfd3000c01v1Entry ::=
			SEQUENCE {
				vfd3000c01v1Index
				ModuleIndex,
				vfd3000c01v1MainOutInput
				ChgOverInput2,
				vfd3000c01v1MainOutInputTrapEnable
				AlarmEnable,
				vfd3000c01v1OutInput
				ChgOverInput2,
				vfd3000c01v1OutInputTrapEnable
				AlarmEnable,
				vfd3000c01v1ControlMode
				Bit0Gpi1Reg,
				vfd3000c01v1HideOsd
				Bit0No1Yes,
				vfd3000c01v1FixedOsd
				Bit0No1Yes,
				vfd3000c01v1Gpo0MskMaxEq
				BitMask,
				vfd3000c01v1Gpo0MskBadFmt
				BitMask,
				vfd3000c01v1Gpo0MskEdhErr
				BitMask,
				vfd3000c01v1Gpo0MskFreeze
				BitMask,
				vfd3000c01v1Gpo0MskBlack
				BitMask,
				vfd3000c01v1Gpo1MskMaxEq
				BitMask,
				vfd3000c01v1Gpo1MskBadFmt
				BitMask,
				vfd3000c01v1Gpo1MskEdhErr
				BitMask,
				vfd3000c01v1Gpo1MskFreeze
				BitMask,
				vfd3000c01v1Gpo1MskBlack
				BitMask,
				vfd3000c01v1Gpo2MskImageD
				BitMask,
				vfd3000c01v1Gpo2MskLevelD
				BitMask,
				vfd3000c01v1Gpo3MskMaxEq
				BitMask,
				vfd3000c01v1Gpo3MskBadFmt
				BitMask,
				vfd3000c01v1Gpo3MskEdhErr
				BitMask,
				vfd3000c01v1Gpo3MskFreeze
				BitMask,
				vfd3000c01v1Gpo3MskBlack
				BitMask,
				vfd3000c01v1BlackLevel
				Uint8,
				vfd3000c01v1ImageDispThres
				Uint8,
				vfd3000c01v1PeakDispThres
				Uint8,
				vfd3000c01v1BlckFrzTimeout
				DelayFram2,
				vfd3000c01v1MaxEqMMask
				BitMask,
				vfd3000c01v1BadFmtMMask
				BitMask,
				vfd3000c01v1EdhErrMMask
				BitMask,
				vfd3000c01v1FreezeMMask
				BitMask,
				vfd3000c01v1BlackMMask
				BitMask,
				vfd3000c01v1MaxEqRMask
				BitMask,
				vfd3000c01v1BadFmtRMask
				BitMask,
				vfd3000c01v1EdhErrRMask
				BitMask,
				vfd3000c01v1FreezeRMask
				BitMask,
				vfd3000c01v1BlackRMask
				BitMask,
				vfd3000c01v1ImageDispMask
				BitMask,
				vfd3000c01v1LevelDispMask
				BitMask,
				vfd3000c01v1MaxEqM
				BitFail,
				vfd3000c01v1MaxEqMTrapEnable
				AlarmEnable,
				vfd3000c01v1BadFmtM
				BitFail,
				vfd3000c01v1BadFmtMTrapEnable
				AlarmEnable,
				vfd3000c01v1EdhErrM
				BitFail,
				vfd3000c01v1EdhErrMTrapEnable
				AlarmEnable,
				vfd3000c01v1BlackM
				BitFail,
				vfd3000c01v1BlackMTrapEnable
				AlarmEnable,
				vfd3000c01v1FreezeM
				BitFail,
				vfd3000c01v1FreezeMTrapEnable
				AlarmEnable,
				vfd3000c01v1MaxEqR
				BitFail,
				vfd3000c01v1MaxEqRTrapEnable
				AlarmEnable,
				vfd3000c01v1BadFmtR
				BitFail,
				vfd3000c01v1BadFmtRTrapEnable
				AlarmEnable,
				vfd3000c01v1EdhErrR
				BitFail,
				vfd3000c01v1EdhErrRTrapEnable
				AlarmEnable,
				vfd3000c01v1BlackR
				BitFail,
				vfd3000c01v1BlackRTrapEnable
				AlarmEnable,
				vfd3000c01v1FreezeR
				BitFail,
				vfd3000c01v1FreezeRTrapEnable
				AlarmEnable,
				vfd3000c01v1ImageDisp
				Uint8,
				vfd3000c01v1PeakDisp
				Uint8
			 }

		-- 1.3.6.1.4.1.10106.3.101291.1.1.1
		vfd3000c01v1Index OBJECT-TYPE
			SYNTAX ModuleIndex
			MAX-ACCESS read-only
			STATUS current
			DESCRIPTION
				"Index of VFD3000C01V1 Table"
		::= { vfd3000c01v1Entry 1 }

		-- 1.3.6.1.4.1.10106.3.101291.1.1.3
		vfd3000c01v1MainOutInput OBJECT-TYPE
			SYNTAX ChgOverInput2
			MAX-ACCESS read-write
			STATUS current
			DESCRIPTION
				"Selected input on main out"
		::= { vfd3000c01v1Entry 3 }

		-- 1.3.6.1.4.1.10106.3.101291.1.1.4
		vfd3000c01v1MainOutInputTrapEnable OBJECT-TYPE
			SYNTAX AlarmEnable
			MAX-ACCESS read-write
			STATUS current
			DESCRIPTION
				"Selected input on main out Trap Enable"
		::= { vfd3000c01v1Entry 4 }

		-- 1.3.6.1.4.1.10106.3.101291.1.1.5
		vfd3000c01v1OutInput OBJECT-TYPE
			SYNTAX ChgOverInput2
			MAX-ACCESS read-write
			STATUS current
			DESCRIPTION
				"Selected input on out"
		::= { vfd3000c01v1Entry 5 }

		-- 1.3.6.1.4.1.10106.3.101291.1.1.6
		vfd3000c01v1OutInputTrapEnable OBJECT-TYPE
			SYNTAX AlarmEnable
			MAX-ACCESS read-write
			STATUS current
			DESCRIPTION
				"Selected input on out Trap Enable"
		::= { vfd3000c01v1Entry 6 }

		-- 1.3.6.1.4.1.10106.3.101291.1.1.7
		vfd3000c01v1ControlMode OBJECT-TYPE
			SYNTAX Bit0Gpi1Reg
			MAX-ACCESS read-write
			STATUS current
			DESCRIPTION
				"Selects how to make the selection of the input asigned to each output"
		::= { vfd3000c01v1Entry 7 }

		-- 1.3.6.1.4.1.10106.3.101291.1.1.9
		vfd3000c01v1HideOsd OBJECT-TYPE
			SYNTAX Bit0No1Yes
			MAX-ACCESS read-write
			STATUS current
			DESCRIPTION
				"Allows hiding the On Screen Display (OSD)"
		::= { vfd3000c01v1Entry 9 }

		-- 1.3.6.1.4.1.10106.3.101291.1.1.11
		vfd3000c01v1FixedOsd OBJECT-TYPE
			SYNTAX Bit0No1Yes
			MAX-ACCESS read-write
			STATUS current
			DESCRIPTION
				"Allows selecting between fixed and temporized OSD"
		::= { vfd3000c01v1Entry 11 }

		-- 1.3.6.1.4.1.10106.3.101291.1.1.13
		vfd3000c01v1Gpo0MskMaxEq OBJECT-TYPE
			SYNTAX BitMask
			MAX-ACCESS read-write
			STATUS current
			DESCRIPTION
				"Selects if GPO0 activates when main input reaches maximun equalization level"
		::= { vfd3000c01v1Entry 13 }

		-- 1.3.6.1.4.1.10106.3.101291.1.1.15
		vfd3000c01v1Gpo0MskBadFmt OBJECT-TYPE
			SYNTAX BitMask
			MAX-ACCESS read-write
			STATUS current
			DESCRIPTION
				"Selects if GPO0 activates when a bad format is detected on main input"
		::= { vfd3000c01v1Entry 15 }

		-- 1.3.6.1.4.1.10106.3.101291.1.1.17
		vfd3000c01v1Gpo0MskEdhErr OBJECT-TYPE
			SYNTAX BitMask
			MAX-ACCESS read-write
			STATUS current
			DESCRIPTION
				"Selects if GPO0 activates when EDH erros are detected on main input"
		::= { vfd3000c01v1Entry 17 }

		-- 1.3.6.1.4.1.10106.3.101291.1.1.19
		vfd3000c01v1Gpo0MskFreeze OBJECT-TYPE
			SYNTAX BitMask
			MAX-ACCESS read-write
			STATUS current
			DESCRIPTION
				"Selects if GPO0 activates when main input is freeze"
		::= { vfd3000c01v1Entry 19 }

		-- 1.3.6.1.4.1.10106.3.101291.1.1.21
		vfd3000c01v1Gpo0MskBlack OBJECT-TYPE
			SYNTAX BitMask
			MAX-ACCESS read-write
			STATUS current
			DESCRIPTION
				"Selects if GPO0 activates when main input is black"
		::= { vfd3000c01v1Entry 21 }

		-- 1.3.6.1.4.1.10106.3.101291.1.1.23
		vfd3000c01v1Gpo1MskMaxEq OBJECT-TYPE
			SYNTAX BitMask
			MAX-ACCESS read-write
			STATUS current
			DESCRIPTION
				"Selects if GPO1 activates when reserve input reaches maximun equalization level"
		::= { vfd3000c01v1Entry 23 }

		-- 1.3.6.1.4.1.10106.3.101291.1.1.25
		vfd3000c01v1Gpo1MskBadFmt OBJECT-TYPE
			SYNTAX BitMask
			MAX-ACCESS read-write
			STATUS current
			DESCRIPTION
				"Selects if GPO1 activates when a bad format is detected on reserve input"
		::= { vfd3000c01v1Entry 25 }

		-- 1.3.6.1.4.1.10106.3.101291.1.1.27
		vfd3000c01v1Gpo1MskEdhErr OBJECT-TYPE
			SYNTAX BitMask
			MAX-ACCESS read-write
			STATUS current
			DESCRIPTION
				"Selects if GPO1 activates when EDH erros are detected on reserve input"
		::= { vfd3000c01v1Entry 27 }

		-- 1.3.6.1.4.1.10106.3.101291.1.1.29
		vfd3000c01v1Gpo1MskFreeze OBJECT-TYPE
			SYNTAX BitMask
			MAX-ACCESS read-write
			STATUS current
			DESCRIPTION
				"Selects if GPO1 activates when reserve input is freeze"
		::= { vfd3000c01v1Entry 29 }

		-- 1.3.6.1.4.1.10106.3.101291.1.1.31
		vfd3000c01v1Gpo1MskBlack OBJECT-TYPE
			SYNTAX BitMask
			MAX-ACCESS read-write
			STATUS current
			DESCRIPTION
				"Selects if GPO1 activates when reserve input is black"
		::= { vfd3000c01v1Entry 31 }

		-- 1.3.6.1.4.1.10106.3.101291.1.1.33
		vfd3000c01v1Gpo2MskImageD OBJECT-TYPE
			SYNTAX BitMask
			MAX-ACCESS read-write
			STATUS current
			DESCRIPTION
				"Selects if GPO2 activates when image dispartity exceeds threshold level"
		::= { vfd3000c01v1Entry 33 }

		-- 1.3.6.1.4.1.10106.3.101291.1.1.35
		vfd3000c01v1Gpo2MskLevelD OBJECT-TYPE
			SYNTAX BitMask
			MAX-ACCESS read-write
			STATUS current
			DESCRIPTION
				"Selects if GPO2 activates when peak level dispartity exceeds threshold level"
		::= { vfd3000c01v1Entry 35 }

		-- 1.3.6.1.4.1.10106.3.101291.1.1.37
		vfd3000c01v1Gpo3MskMaxEq OBJECT-TYPE
			SYNTAX BitMask
			MAX-ACCESS read-write
			STATUS current
			DESCRIPTION
				"Selects if GPO3 activates when main input reaches maximun equalization level"
		::= { vfd3000c01v1Entry 37 }

		-- 1.3.6.1.4.1.10106.3.101291.1.1.39
		vfd3000c01v1Gpo3MskBadFmt OBJECT-TYPE
			SYNTAX BitMask
			MAX-ACCESS read-write
			STATUS current
			DESCRIPTION
				"Selects if GPO3 activates when a bad format is detected on main input"
		::= { vfd3000c01v1Entry 39 }

		-- 1.3.6.1.4.1.10106.3.101291.1.1.41
		vfd3000c01v1Gpo3MskEdhErr OBJECT-TYPE
			SYNTAX BitMask
			MAX-ACCESS read-write
			STATUS current
			DESCRIPTION
				"Selects if GPO3 activates when EDH erros are detected on main input"
		::= { vfd3000c01v1Entry 41 }

		-- 1.3.6.1.4.1.10106.3.101291.1.1.43
		vfd3000c01v1Gpo3MskFreeze OBJECT-TYPE
			SYNTAX BitMask
			MAX-ACCESS read-write
			STATUS current
			DESCRIPTION
				"Selects if GPO3 activates when main input is freeze"
		::= { vfd3000c01v1Entry 43 }

		-- 1.3.6.1.4.1.10106.3.101291.1.1.45
		vfd3000c01v1Gpo3MskBlack OBJECT-TYPE
			SYNTAX BitMask
			MAX-ACCESS read-write
			STATUS current
			DESCRIPTION
				"Selects if GPO3 activates when main input is black"
		::= { vfd3000c01v1Entry 45 }

		-- 1.3.6.1.4.1.10106.3.101291.1.1.47
		vfd3000c01v1BlackLevel OBJECT-TYPE
			SYNTAX Uint8
			MAX-ACCESS read-write
			STATUS current
			DESCRIPTION
				"Allows adjusting the black level"
		::= { vfd3000c01v1Entry 47 }

		-- 1.3.6.1.4.1.10106.3.101291.1.1.49
		vfd3000c01v1ImageDispThres OBJECT-TYPE
			SYNTAX Uint8
			MAX-ACCESS read-write
			STATUS current
			DESCRIPTION
				"Allows adjusting image disparity threshold"
		::= { vfd3000c01v1Entry 49 }

		-- 1.3.6.1.4.1.10106.3.101291.1.1.51
		vfd3000c01v1PeakDispThres OBJECT-TYPE
			SYNTAX Uint8
			MAX-ACCESS read-write
			STATUS current
			DESCRIPTION
				"Allows adjusting peak disparity threshold"
		::= { vfd3000c01v1Entry 51 }

		-- 1.3.6.1.4.1.10106.3.101291.1.1.53
		vfd3000c01v1BlckFrzTimeout OBJECT-TYPE
			SYNTAX DelayFram2
			MAX-ACCESS read-write
			STATUS current
			DESCRIPTION
				"Allows selecting the fail detection timeout"
		::= { vfd3000c01v1Entry 53 }

		-- 1.3.6.1.4.1.10106.3.101291.1.1.55
		vfd3000c01v1MaxEqMMask OBJECT-TYPE
			SYNTAX BitMask
			MAX-ACCESS read-write
			STATUS current
			DESCRIPTION
				"Allows masking maximum equalization fail"
		::= { vfd3000c01v1Entry 55 }

		-- 1.3.6.1.4.1.10106.3.101291.1.1.57
		vfd3000c01v1BadFmtMMask OBJECT-TYPE
			SYNTAX BitMask
			MAX-ACCESS read-write
			STATUS current
			DESCRIPTION
				"Allows masking the bad SDI format fail"
		::= { vfd3000c01v1Entry 57 }

		-- 1.3.6.1.4.1.10106.3.101291.1.1.59
		vfd3000c01v1EdhErrMMask OBJECT-TYPE
			SYNTAX BitMask
			MAX-ACCESS read-write
			STATUS current
			DESCRIPTION
				"Allows masking the EDH error fail"
		::= { vfd3000c01v1Entry 59 }

		-- 1.3.6.1.4.1.10106.3.101291.1.1.61
		vfd3000c01v1FreezeMMask OBJECT-TYPE
			SYNTAX BitMask
			MAX-ACCESS read-write
			STATUS current
			DESCRIPTION
				"Allows masking the freeze image fail"
		::= { vfd3000c01v1Entry 61 }

		-- 1.3.6.1.4.1.10106.3.101291.1.1.63
		vfd3000c01v1BlackMMask OBJECT-TYPE
			SYNTAX BitMask
			MAX-ACCESS read-write
			STATUS current
			DESCRIPTION
				"Allows masking the black pattern fail"
		::= { vfd3000c01v1Entry 63 }

		-- 1.3.6.1.4.1.10106.3.101291.1.1.65
		vfd3000c01v1MaxEqRMask OBJECT-TYPE
			SYNTAX BitMask
			MAX-ACCESS read-write
			STATUS current
			DESCRIPTION
				"Allows masking the no SDI signal fail"
		::= { vfd3000c01v1Entry 65 }

		-- 1.3.6.1.4.1.10106.3.101291.1.1.67
		vfd3000c01v1BadFmtRMask OBJECT-TYPE
			SYNTAX BitMask
			MAX-ACCESS read-write
			STATUS current
			DESCRIPTION
				"Allows masking the bad SDI format fail"
		::= { vfd3000c01v1Entry 67 }

		-- 1.3.6.1.4.1.10106.3.101291.1.1.69
		vfd3000c01v1EdhErrRMask OBJECT-TYPE
			SYNTAX BitMask
			MAX-ACCESS read-write
			STATUS current
			DESCRIPTION
				"Allows masking the EDH error fail"
		::= { vfd3000c01v1Entry 69 }

		-- 1.3.6.1.4.1.10106.3.101291.1.1.71
		vfd3000c01v1FreezeRMask OBJECT-TYPE
			SYNTAX BitMask
			MAX-ACCESS read-write
			STATUS current
			DESCRIPTION
				"Allows masking the freeze image fail"
		::= { vfd3000c01v1Entry 71 }

		-- 1.3.6.1.4.1.10106.3.101291.1.1.73
		vfd3000c01v1BlackRMask OBJECT-TYPE
			SYNTAX BitMask
			MAX-ACCESS read-write
			STATUS current
			DESCRIPTION
				"Allows masking the black pattern fail"
		::= { vfd3000c01v1Entry 73 }

		-- 1.3.6.1.4.1.10106.3.101291.1.1.75
		vfd3000c01v1ImageDispMask OBJECT-TYPE
			SYNTAX BitMask
			MAX-ACCESS read-write
			STATUS current
			DESCRIPTION
				"Allows masking the image disparity fail"
		::= { vfd3000c01v1Entry 75 }

		-- 1.3.6.1.4.1.10106.3.101291.1.1.77
		vfd3000c01v1LevelDispMask OBJECT-TYPE
			SYNTAX BitMask
			MAX-ACCESS read-write
			STATUS current
			DESCRIPTION
				"Allows masking the peak level disparity fail"
		::= { vfd3000c01v1Entry 77 }

		-- 1.3.6.1.4.1.10106.3.101291.1.1.79
		vfd3000c01v1MaxEqM OBJECT-TYPE
			SYNTAX BitFail
			MAX-ACCESS read-only
			STATUS current
			DESCRIPTION
				"Indicates maximum equalization fail"
		::= { vfd3000c01v1Entry 79 }

		-- 1.3.6.1.4.1.10106.3.101291.1.1.80
		vfd3000c01v1MaxEqMTrapEnable OBJECT-TYPE
			SYNTAX AlarmEnable
			MAX-ACCESS read-write
			STATUS current
			DESCRIPTION
				"Indicates maximum equalization fail Trap Enable"
		::= { vfd3000c01v1Entry 80 }

		-- 1.3.6.1.4.1.10106.3.101291.1.1.81
		vfd3000c01v1BadFmtM OBJECT-TYPE
			SYNTAX BitFail
			MAX-ACCESS read-only
			STATUS current
			DESCRIPTION
				"Indicates bad SDI format fail"
		::= { vfd3000c01v1Entry 81 }

		-- 1.3.6.1.4.1.10106.3.101291.1.1.82
		vfd3000c01v1BadFmtMTrapEnable OBJECT-TYPE
			SYNTAX AlarmEnable
			MAX-ACCESS read-write
			STATUS current
			DESCRIPTION
				"Indicates bad SDI format fail Trap Enable"
		::= { vfd3000c01v1Entry 82 }

		-- 1.3.6.1.4.1.10106.3.101291.1.1.83
		vfd3000c01v1EdhErrM OBJECT-TYPE
			SYNTAX BitFail
			MAX-ACCESS read-only
			STATUS current
			DESCRIPTION
				"Indicates EDH error fail"
		::= { vfd3000c01v1Entry 83 }

		-- 1.3.6.1.4.1.10106.3.101291.1.1.84
		vfd3000c01v1EdhErrMTrapEnable OBJECT-TYPE
			SYNTAX AlarmEnable
			MAX-ACCESS read-write
			STATUS current
			DESCRIPTION
				"Indicates EDH error fail Trap Enable"
		::= { vfd3000c01v1Entry 84 }

		-- 1.3.6.1.4.1.10106.3.101291.1.1.85
		vfd3000c01v1BlackM OBJECT-TYPE
			SYNTAX BitFail
			MAX-ACCESS read-only
			STATUS current
			DESCRIPTION
				"Indicates black pattern fail"
		::= { vfd3000c01v1Entry 85 }

		-- 1.3.6.1.4.1.10106.3.101291.1.1.86
		vfd3000c01v1BlackMTrapEnable OBJECT-TYPE
			SYNTAX AlarmEnable
			MAX-ACCESS read-write
			STATUS current
			DESCRIPTION
				"Indicates black pattern fail Trap Enable"
		::= { vfd3000c01v1Entry 86 }

		-- 1.3.6.1.4.1.10106.3.101291.1.1.87
		vfd3000c01v1FreezeM OBJECT-TYPE
			SYNTAX BitFail
			MAX-ACCESS read-only
			STATUS current
			DESCRIPTION
				"Indicates freeze image fail"
		::= { vfd3000c01v1Entry 87 }

		-- 1.3.6.1.4.1.10106.3.101291.1.1.88
		vfd3000c01v1FreezeMTrapEnable OBJECT-TYPE
			SYNTAX AlarmEnable
			MAX-ACCESS read-write
			STATUS current
			DESCRIPTION
				"Indicates freeze image fail Trap Enable"
		::= { vfd3000c01v1Entry 88 }

		-- 1.3.6.1.4.1.10106.3.101291.1.1.89
		vfd3000c01v1MaxEqR OBJECT-TYPE
			SYNTAX BitFail
			MAX-ACCESS read-only
			STATUS current
			DESCRIPTION
				"Indicates maximum equalization fail"
		::= { vfd3000c01v1Entry 89 }

		-- 1.3.6.1.4.1.10106.3.101291.1.1.90
		vfd3000c01v1MaxEqRTrapEnable OBJECT-TYPE
			SYNTAX AlarmEnable
			MAX-ACCESS read-write
			STATUS current
			DESCRIPTION
				"Indicates maximum equalization fail Trap Enable"
		::= { vfd3000c01v1Entry 90 }

		-- 1.3.6.1.4.1.10106.3.101291.1.1.91
		vfd3000c01v1BadFmtR OBJECT-TYPE
			SYNTAX BitFail
			MAX-ACCESS read-only
			STATUS current
			DESCRIPTION
				"Indicates bad SDI format fail"
		::= { vfd3000c01v1Entry 91 }

		-- 1.3.6.1.4.1.10106.3.101291.1.1.92
		vfd3000c01v1BadFmtRTrapEnable OBJECT-TYPE
			SYNTAX AlarmEnable
			MAX-ACCESS read-write
			STATUS current
			DESCRIPTION
				"Indicates bad SDI format fail Trap Enable"
		::= { vfd3000c01v1Entry 92 }

		-- 1.3.6.1.4.1.10106.3.101291.1.1.93
		vfd3000c01v1EdhErrR OBJECT-TYPE
			SYNTAX BitFail
			MAX-ACCESS read-only
			STATUS current
			DESCRIPTION
				"Indicates EDH error fail"
		::= { vfd3000c01v1Entry 93 }

		-- 1.3.6.1.4.1.10106.3.101291.1.1.94
		vfd3000c01v1EdhErrRTrapEnable OBJECT-TYPE
			SYNTAX AlarmEnable
			MAX-ACCESS read-write
			STATUS current
			DESCRIPTION
				"Indicates EDH error fail Trap Enable"
		::= { vfd3000c01v1Entry 94 }

		-- 1.3.6.1.4.1.10106.3.101291.1.1.95
		vfd3000c01v1BlackR OBJECT-TYPE
			SYNTAX BitFail
			MAX-ACCESS read-only
			STATUS current
			DESCRIPTION
				"Indicates black pattern fail"
		::= { vfd3000c01v1Entry 95 }

		-- 1.3.6.1.4.1.10106.3.101291.1.1.96
		vfd3000c01v1BlackRTrapEnable OBJECT-TYPE
			SYNTAX AlarmEnable
			MAX-ACCESS read-write
			STATUS current
			DESCRIPTION
				"Indicates black pattern fail Trap Enable"
		::= { vfd3000c01v1Entry 96 }

		-- 1.3.6.1.4.1.10106.3.101291.1.1.97
		vfd3000c01v1FreezeR OBJECT-TYPE
			SYNTAX BitFail
			MAX-ACCESS read-only
			STATUS current
			DESCRIPTION
				"Indicates freeze image fail"
		::= { vfd3000c01v1Entry 97 }

		-- 1.3.6.1.4.1.10106.3.101291.1.1.98
		vfd3000c01v1FreezeRTrapEnable OBJECT-TYPE
			SYNTAX AlarmEnable
			MAX-ACCESS read-write
			STATUS current
			DESCRIPTION
				"Indicates freeze image fail Trap Enable"
		::= { vfd3000c01v1Entry 98 }

		-- 1.3.6.1.4.1.10106.3.101291.1.1.99
		vfd3000c01v1ImageDisp OBJECT-TYPE
			SYNTAX Uint8
			MAX-ACCESS read-only
			STATUS current
			DESCRIPTION
				"Indicates image disparity"
		::= { vfd3000c01v1Entry 99 }

		-- 1.3.6.1.4.1.10106.3.101291.1.1.101
		vfd3000c01v1PeakDisp OBJECT-TYPE
			SYNTAX Uint8
			MAX-ACCESS read-only
			STATUS current
			DESCRIPTION
				"Indicates peak level disparity"
		::= { vfd3000c01v1Entry 101 }

		-- 1.3.6.1.4.1.10106.3.167501
		dar3000p01v1 OBJECT IDENTIFIER ::= { albalaProducts 167501 }

		-- 1.3.6.1.4.1.10106.3.167501.1
		dar3000p01v1Table  OBJECT-TYPE
			SYNTAX SEQUENCE OF Dar3000p01v1Entry
			MAX-ACCESS not-accessible
			STATUS current
			DESCRIPTION
				"Module  DAR3000P01V1 Table"
			::= { dar3000p01v1 1 }

		-- 1.3.6.1.4.1.10106.3.167501.1.1
		dar3000p01v1Entry  OBJECT-TYPE
			SYNTAX Dar3000p01v1Entry
			MAX-ACCESS not-accessible
			STATUS current
			DESCRIPTION
				"Module DAR3000P01V1 Entry"
			INDEX { dar3000p01v1Index }
			::= { dar3000p01v1Table 1 }

			Dar3000p01v1Entry ::=
			SEQUENCE {
				dar3000p01v1Index
				ModuleIndex,
				dar3000p01v1Bits
				Bit020124,
				dar3000p01v10dbLevel
				Bit00db1Nxdb,
				dar3000p01v1Mode
				Bit0Aut1Man,
				dar3000p01v1InputRef
				AudioRef4,
				dar3000p01v1OutputFreq
				AudioSelFreq1,
				dar3000p01v1DipEnable
				Bit0Dis1Ena,
				dar3000p01v1OptLevel
				Bit0N181N20,
				dar3000p01v1AudFreqCh1L
				AudioFreq1,
				dar3000p01v1AudFreqCh1R
				AudioFreq1,
				dar3000p01v1AudFreqCh2L
				AudioFreq1,
				dar3000p01v1AudFreqCh2R
				AudioFreq1,
				dar3000p01v1OutFreq
				AudioSelFreq2,
				dar3000p01v1UnlockAes
				BitFail,
				dar3000p01v1UnlockAesTrapEnable
				AlarmEnable,
				dar3000p01v1UnlockVid
				BitFail,
				dar3000p01v1UnlockVidTrapEnable
				AlarmEnable,
				dar3000p01v1UnlockWclk
				BitFail,
				dar3000p01v1UnlockWclkTrapEnable
				AlarmEnable,
				dar3000p01v1NoAes
				BitFail,
				dar3000p01v1NoAesTrapEnable
				AlarmEnable,
				dar3000p01v1NoVid
				BitFail,
				dar3000p01v1NoVidTrapEnable
				AlarmEnable,
				dar3000p01v1NoWclk
				BitFail,
				dar3000p01v1NoWclkTrapEnable
				AlarmEnable,
				dar3000p01v1SilenceL
				Bit0No1Yes,
				dar3000p01v1SilenceR
				Bit0No1Yes,
				dar3000p01v1SilenceCh1
				Bit0No1Yes,
				dar3000p01v1SilenceCh2
				Bit0No1Yes
			 }

		-- 1.3.6.1.4.1.10106.3.101291.1.1.1
		dar3000p01v1Index OBJECT-TYPE
			SYNTAX ModuleIndex
			MAX-ACCESS read-only
			STATUS current
			DESCRIPTION
				"Index of DAR3000P01V1 Table"
		::= { dar3000p01v1Entry 1 }

		-- 1.3.6.1.4.1.10106.3.101291.1.1.3
		dar3000p01v1Bits OBJECT-TYPE
			SYNTAX Bit020124
			MAX-ACCESS read-write
			STATUS current
			DESCRIPTION
				"Allows selecting the number of bits"
		::= { dar3000p01v1Entry 3 }

		-- 1.3.6.1.4.1.10106.3.101291.1.1.5
		dar3000p01v10dbLevel OBJECT-TYPE
			SYNTAX Bit00db1Nxdb
			MAX-ACCESS read-write
			STATUS current
			DESCRIPTION
				"Allows selecting the output audio level"
		::= { dar3000p01v1Entry 5 }

		-- 1.3.6.1.4.1.10106.3.101291.1.1.7
		dar3000p01v1Mode OBJECT-TYPE
			SYNTAX Bit0Aut1Man
			MAX-ACCESS read-write
			STATUS current
			DESCRIPTION
				"Allows selecting the reference selection mode"
		::= { dar3000p01v1Entry 7 }

		-- 1.3.6.1.4.1.10106.3.101291.1.1.9
		dar3000p01v1InputRef OBJECT-TYPE
			SYNTAX AudioRef4
			MAX-ACCESS read-write
			STATUS current
			DESCRIPTION
				"Allows selecting the reference input in manual mode"
		::= { dar3000p01v1Entry 9 }

		-- 1.3.6.1.4.1.10106.3.101291.1.1.11
		dar3000p01v1OutputFreq OBJECT-TYPE
			SYNTAX AudioSelFreq1
			MAX-ACCESS read-write
			STATUS current
			DESCRIPTION
				"Allows selecting the output samplign frequency in manual mode"
		::= { dar3000p01v1Entry 11 }

		-- 1.3.6.1.4.1.10106.3.101291.1.1.13
		dar3000p01v1DipEnable OBJECT-TYPE
			SYNTAX Bit0Dis1Ena
			MAX-ACCESS read-write
			STATUS current
			DESCRIPTION
				"Allows enabling the insertion of silences for channel identification"
		::= { dar3000p01v1Entry 13 }

		-- 1.3.6.1.4.1.10106.3.101291.1.1.15
		dar3000p01v1OptLevel OBJECT-TYPE
			SYNTAX Bit0N181N20
			MAX-ACCESS read-write
			STATUS current
			DESCRIPTION
				"Allows selecting the output audio level between -18 dBfs and -20dBfs"
		::= { dar3000p01v1Entry 15 }

		-- 1.3.6.1.4.1.10106.3.101291.1.1.17
		dar3000p01v1AudFreqCh1L OBJECT-TYPE
			SYNTAX AudioFreq1
			MAX-ACCESS read-write
			STATUS current
			DESCRIPTION
				"Allows selecting OUT1/OUT2  L audio frequency"
		::= { dar3000p01v1Entry 17 }

		-- 1.3.6.1.4.1.10106.3.101291.1.1.19
		dar3000p01v1AudFreqCh1R OBJECT-TYPE
			SYNTAX AudioFreq1
			MAX-ACCESS read-write
			STATUS current
			DESCRIPTION
				"Allows selecting OUT1/OUT2  R audio frequency"
		::= { dar3000p01v1Entry 19 }

		-- 1.3.6.1.4.1.10106.3.101291.1.1.21
		dar3000p01v1AudFreqCh2L OBJECT-TYPE
			SYNTAX AudioFreq1
			MAX-ACCESS read-write
			STATUS current
			DESCRIPTION
				"Allows selecting OUT3/OUT4  L audio frequency"
		::= { dar3000p01v1Entry 21 }

		-- 1.3.6.1.4.1.10106.3.101291.1.1.23
		dar3000p01v1AudFreqCh2R OBJECT-TYPE
			SYNTAX AudioFreq1
			MAX-ACCESS read-write
			STATUS current
			DESCRIPTION
				"Allows selecting OUT3/OUT4  R audio frequency"
		::= { dar3000p01v1Entry 23 }

		-- 1.3.6.1.4.1.10106.3.101291.1.1.25
		dar3000p01v1OutFreq OBJECT-TYPE
			SYNTAX AudioSelFreq2
			MAX-ACCESS read-only
			STATUS current
			DESCRIPTION
				"Indicates the actual output sampling frequency"
		::= { dar3000p01v1Entry 25 }

		-- 1.3.6.1.4.1.10106.3.101291.1.1.27
		dar3000p01v1UnlockAes OBJECT-TYPE
			SYNTAX BitFail
			MAX-ACCESS read-only
			STATUS current
			DESCRIPTION
				"Indicates AES reference unlock fail"
		::= { dar3000p01v1Entry 27 }

		-- 1.3.6.1.4.1.10106.3.101291.1.1.28
		dar3000p01v1UnlockAesTrapEnable OBJECT-TYPE
			SYNTAX AlarmEnable
			MAX-ACCESS read-write
			STATUS current
			DESCRIPTION
				"Indicates AES reference unlock fail Trap Enable"
		::= { dar3000p01v1Entry 28 }

		-- 1.3.6.1.4.1.10106.3.101291.1.1.29
		dar3000p01v1UnlockVid OBJECT-TYPE
			SYNTAX BitFail
			MAX-ACCESS read-only
			STATUS current
			DESCRIPTION
				"Indicates video reference unlock fail"
		::= { dar3000p01v1Entry 29 }

		-- 1.3.6.1.4.1.10106.3.101291.1.1.30
		dar3000p01v1UnlockVidTrapEnable OBJECT-TYPE
			SYNTAX AlarmEnable
			MAX-ACCESS read-write
			STATUS current
			DESCRIPTION
				"Indicates video reference unlock fail Trap Enable"
		::= { dar3000p01v1Entry 30 }

		-- 1.3.6.1.4.1.10106.3.101291.1.1.31
		dar3000p01v1UnlockWclk OBJECT-TYPE
			SYNTAX BitFail
			MAX-ACCESS read-only
			STATUS current
			DESCRIPTION
				"Indicates Wordclock reference unlock fail"
		::= { dar3000p01v1Entry 31 }

		-- 1.3.6.1.4.1.10106.3.101291.1.1.32
		dar3000p01v1UnlockWclkTrapEnable OBJECT-TYPE
			SYNTAX AlarmEnable
			MAX-ACCESS read-write
			STATUS current
			DESCRIPTION
				"Indicates Wordclock reference unlock fail Trap Enable"
		::= { dar3000p01v1Entry 32 }

		-- 1.3.6.1.4.1.10106.3.101291.1.1.33
		dar3000p01v1NoAes OBJECT-TYPE
			SYNTAX BitFail
			MAX-ACCESS read-only
			STATUS current
			DESCRIPTION
				"Indicates no AES reference signal"
		::= { dar3000p01v1Entry 33 }

		-- 1.3.6.1.4.1.10106.3.101291.1.1.34
		dar3000p01v1NoAesTrapEnable OBJECT-TYPE
			SYNTAX AlarmEnable
			MAX-ACCESS read-write
			STATUS current
			DESCRIPTION
				"Indicates no AES reference signal Trap Enable"
		::= { dar3000p01v1Entry 34 }

		-- 1.3.6.1.4.1.10106.3.101291.1.1.35
		dar3000p01v1NoVid OBJECT-TYPE
			SYNTAX BitFail
			MAX-ACCESS read-only
			STATUS current
			DESCRIPTION
				"Indicates no video reference signal"
		::= { dar3000p01v1Entry 35 }

		-- 1.3.6.1.4.1.10106.3.101291.1.1.36
		dar3000p01v1NoVidTrapEnable OBJECT-TYPE
			SYNTAX AlarmEnable
			MAX-ACCESS read-write
			STATUS current
			DESCRIPTION
				"Indicates no video reference signal Trap Enable"
		::= { dar3000p01v1Entry 36 }

		-- 1.3.6.1.4.1.10106.3.101291.1.1.37
		dar3000p01v1NoWclk OBJECT-TYPE
			SYNTAX BitFail
			MAX-ACCESS read-only
			STATUS current
			DESCRIPTION
				"Indicates no Wordclock reference signal"
		::= { dar3000p01v1Entry 37 }

		-- 1.3.6.1.4.1.10106.3.101291.1.1.38
		dar3000p01v1NoWclkTrapEnable OBJECT-TYPE
			SYNTAX AlarmEnable
			MAX-ACCESS read-write
			STATUS current
			DESCRIPTION
				"Indicates no Wordclock reference signal Trap Enable"
		::= { dar3000p01v1Entry 38 }

		-- 1.3.6.1.4.1.10106.3.101291.1.1.39
		dar3000p01v1SilenceL OBJECT-TYPE
			SYNTAX Bit0No1Yes
			MAX-ACCESS read-write
			STATUS current
			DESCRIPTION
				"Allows muting left channel"
		::= { dar3000p01v1Entry 39 }

		-- 1.3.6.1.4.1.10106.3.101291.1.1.41
		dar3000p01v1SilenceR OBJECT-TYPE
			SYNTAX Bit0No1Yes
			MAX-ACCESS read-write
			STATUS current
			DESCRIPTION
				"Allows muting right channel"
		::= { dar3000p01v1Entry 41 }

		-- 1.3.6.1.4.1.10106.3.101291.1.1.43
		dar3000p01v1SilenceCh1 OBJECT-TYPE
			SYNTAX Bit0No1Yes
			MAX-ACCESS read-write
			STATUS current
			DESCRIPTION
				"Allows muting OUT1/OUT2"
		::= { dar3000p01v1Entry 43 }

		-- 1.3.6.1.4.1.10106.3.101291.1.1.45
		dar3000p01v1SilenceCh2 OBJECT-TYPE
			SYNTAX Bit0No1Yes
			MAX-ACCESS read-write
			STATUS current
			DESCRIPTION
				"Allows muting OUT3/OUT4"
		::= { dar3000p01v1Entry 45 }

		-- 1.3.6.1.4.1.10106.3.184801
		txt3000p01v1 OBJECT IDENTIFIER ::= { albalaProducts 184801 }

		-- 1.3.6.1.4.1.10106.3.184801.1
		txt3000p01v1Table  OBJECT-TYPE
			SYNTAX SEQUENCE OF Txt3000p01v1Entry
			MAX-ACCESS not-accessible
			STATUS current
			DESCRIPTION
				"Module  TXT3000P01V1 Table"
			::= { txt3000p01v1 1 }

		-- 1.3.6.1.4.1.10106.3.184801.1.1
		txt3000p01v1Entry  OBJECT-TYPE
			SYNTAX Txt3000p01v1Entry
			MAX-ACCESS not-accessible
			STATUS current
			DESCRIPTION
				"Module TXT3000P01V1 Entry"
			INDEX { txt3000p01v1Index }
			::= { txt3000p01v1Table 1 }

			Txt3000p01v1Entry ::=
			SEQUENCE {
				txt3000p01v1Index
				ModuleIndex,
				txt3000p01v1InsEna
				Bit0No1Yes,
				txt3000p01v1Preset
				Uint3,
				txt3000p01v1NoSigPgm
				BitFail,
				txt3000p01v1NoSigPgmTrapEnable
				AlarmEnable,
				txt3000p01v1MaxEqPgm
				BitFail,
				txt3000p01v1EdhErrPgm
				BitFail,
				txt3000p01v1NoSigSrc
				BitFail,
				txt3000p01v1NoSigSrcTrapEnable
				AlarmEnable,
				txt3000p01v1MaxEqSrc
				BitFail,
				txt3000p01v1EdhErrSrc
				BitFail
			 }

		-- 1.3.6.1.4.1.10106.3.101291.1.1.1
		txt3000p01v1Index OBJECT-TYPE
			SYNTAX ModuleIndex
			MAX-ACCESS read-only
			STATUS current
			DESCRIPTION
				"Index of TXT3000P01V1 Table"
		::= { txt3000p01v1Entry 1 }

		-- 1.3.6.1.4.1.10106.3.101291.1.1.3
		txt3000p01v1InsEna OBJECT-TYPE
			SYNTAX Bit0No1Yes
			MAX-ACCESS read-write
			STATUS current
			DESCRIPTION
				"Allows enabling the teletext bridge function"
		::= { txt3000p01v1Entry 3 }

		-- 1.3.6.1.4.1.10106.3.101291.1.1.5
		txt3000p01v1Preset OBJECT-TYPE
			SYNTAX Uint3
			MAX-ACCESS read-write
			STATUS current
			DESCRIPTION
				"Allows selecting the active preset"
		::= { txt3000p01v1Entry 5 }

		-- 1.3.6.1.4.1.10106.3.101291.1.1.7
		txt3000p01v1NoSigPgm OBJECT-TYPE
			SYNTAX BitFail
			MAX-ACCESS read-only
			STATUS current
			DESCRIPTION
				"SDI input signal status"
		::= { txt3000p01v1Entry 7 }

		-- 1.3.6.1.4.1.10106.3.101291.1.1.8
		txt3000p01v1NoSigPgmTrapEnable OBJECT-TYPE
			SYNTAX AlarmEnable
			MAX-ACCESS read-write
			STATUS current
			DESCRIPTION
				"SDI input signal status Trap Enable"
		::= { txt3000p01v1Entry 8 }

		-- 1.3.6.1.4.1.10106.3.101291.1.1.9
		txt3000p01v1MaxEqPgm OBJECT-TYPE
			SYNTAX BitFail
			MAX-ACCESS read-only
			STATUS current
			DESCRIPTION
				"Indicates maximum equalization"
		::= { txt3000p01v1Entry 9 }

		-- 1.3.6.1.4.1.10106.3.101291.1.1.11
		txt3000p01v1EdhErrPgm OBJECT-TYPE
			SYNTAX BitFail
			MAX-ACCESS read-only
			STATUS current
			DESCRIPTION
				"Indicates EDH errors"
		::= { txt3000p01v1Entry 11 }

		-- 1.3.6.1.4.1.10106.3.101291.1.1.13
		txt3000p01v1NoSigSrc OBJECT-TYPE
			SYNTAX BitFail
			MAX-ACCESS read-only
			STATUS current
			DESCRIPTION
				"SDI input signal status"
		::= { txt3000p01v1Entry 13 }

		-- 1.3.6.1.4.1.10106.3.101291.1.1.14
		txt3000p01v1NoSigSrcTrapEnable OBJECT-TYPE
			SYNTAX AlarmEnable
			MAX-ACCESS read-write
			STATUS current
			DESCRIPTION
				"SDI input signal status Trap Enable"
		::= { txt3000p01v1Entry 14 }

		-- 1.3.6.1.4.1.10106.3.101291.1.1.15
		txt3000p01v1MaxEqSrc OBJECT-TYPE
			SYNTAX BitFail
			MAX-ACCESS read-only
			STATUS current
			DESCRIPTION
				"Indicates maximum equalization"
		::= { txt3000p01v1Entry 15 }

		-- 1.3.6.1.4.1.10106.3.101291.1.1.17
		txt3000p01v1EdhErrSrc OBJECT-TYPE
			SYNTAX BitFail
			MAX-ACCESS read-only
			STATUS current
			DESCRIPTION
				"Indicates EDH errors"
		::= { txt3000p01v1Entry 17 }

		-- 1.3.6.1.4.1.10106.3.187601
		dvp3224p01v1 OBJECT IDENTIFIER ::= { albalaProducts 187601 }

		-- 1.3.6.1.4.1.10106.3.187601.1
		dvp3224p01v1Table  OBJECT-TYPE
			SYNTAX SEQUENCE OF Dvp3224p01v1Entry
			MAX-ACCESS not-accessible
			STATUS current
			DESCRIPTION
				"Module  DVP3224P01V1 Table"
			::= { dvp3224p01v1 1 }

		-- 1.3.6.1.4.1.10106.3.187601.1.1
		dvp3224p01v1Entry  OBJECT-TYPE
			SYNTAX Dvp3224p01v1Entry
			MAX-ACCESS not-accessible
			STATUS current
			DESCRIPTION
				"Module DVP3224P01V1 Entry"
			INDEX { dvp3224p01v1Index }
			::= { dvp3224p01v1Table 1 }

			Dvp3224p01v1Entry ::=
			SEQUENCE {
				dvp3224p01v1Index
				ModuleIndex,
				dvp3224p01v1Output1
				Inputs132,
				dvp3224p01v1Output2
				Inputs132,
				dvp3224p01v1Output3
				Inputs132,
				dvp3224p01v1Output4
				Inputs132,
				dvp3224p01v1SwitchTime
				PreselSwTime2,
				dvp3224p01v1NoSync
				BitFail,
				dvp3224p01v1SyncLines
				Bit06251525
			 }

		-- 1.3.6.1.4.1.10106.3.101291.1.1.1
		dvp3224p01v1Index OBJECT-TYPE
			SYNTAX ModuleIndex
			MAX-ACCESS read-only
			STATUS current
			DESCRIPTION
				"Index of DVP3224P01V1 Table"
		::= { dvp3224p01v1Entry 1 }

		-- 1.3.6.1.4.1.10106.3.101291.1.1.3
		dvp3224p01v1Output1 OBJECT-TYPE
			SYNTAX Inputs132
			MAX-ACCESS read-write
			STATUS current
			DESCRIPTION
				"Input routed to output 1"
		::= { dvp3224p01v1Entry 3 }

		-- 1.3.6.1.4.1.10106.3.101291.1.1.5
		dvp3224p01v1Output2 OBJECT-TYPE
			SYNTAX Inputs132
			MAX-ACCESS read-write
			STATUS current
			DESCRIPTION
				"Input routed to output 2"
		::= { dvp3224p01v1Entry 5 }

		-- 1.3.6.1.4.1.10106.3.101291.1.1.7
		dvp3224p01v1Output3 OBJECT-TYPE
			SYNTAX Inputs132
			MAX-ACCESS read-write
			STATUS current
			DESCRIPTION
				"Input routed to output 3"
		::= { dvp3224p01v1Entry 7 }

		-- 1.3.6.1.4.1.10106.3.101291.1.1.9
		dvp3224p01v1Output4 OBJECT-TYPE
			SYNTAX Inputs132
			MAX-ACCESS read-write
			STATUS current
			DESCRIPTION
				"Input routed to output 4"
		::= { dvp3224p01v1Entry 9 }

		-- 1.3.6.1.4.1.10106.3.101291.1.1.11
		dvp3224p01v1SwitchTime OBJECT-TYPE
			SYNTAX PreselSwTime2
			MAX-ACCESS read-write
			STATUS current
			DESCRIPTION
				"Allows selection of switching time"
		::= { dvp3224p01v1Entry 11 }

		-- 1.3.6.1.4.1.10106.3.101291.1.1.13
		dvp3224p01v1NoSync OBJECT-TYPE
			SYNTAX BitFail
			MAX-ACCESS read-only
			STATUS current
			DESCRIPTION
				"Sync presence status"
		::= { dvp3224p01v1Entry 13 }

		-- 1.3.6.1.4.1.10106.3.101291.1.1.15
		dvp3224p01v1SyncLines OBJECT-TYPE
			SYNTAX Bit06251525
			MAX-ACCESS read-only
			STATUS current
			DESCRIPTION
				"Number of lines of sync signal"
		::= { dvp3224p01v1Entry 15 }

		-- 1.3.6.1.4.1.10106.3.195701
		gps3000p01v1 OBJECT IDENTIFIER ::= { albalaProducts 195701 }

		-- 1.3.6.1.4.1.10106.3.195701.1
		gps3000p01v1Table  OBJECT-TYPE
			SYNTAX SEQUENCE OF Gps3000p01v1Entry
			MAX-ACCESS not-accessible
			STATUS current
			DESCRIPTION
				"Module  GPS3000P01V1 Table"
			::= { gps3000p01v1 1 }

		-- 1.3.6.1.4.1.10106.3.195701.1.1
		gps3000p01v1Entry  OBJECT-TYPE
			SYNTAX Gps3000p01v1Entry
			MAX-ACCESS not-accessible
			STATUS current
			DESCRIPTION
				"Module GPS3000P01V1 Entry"
			INDEX { gps3000p01v1Index }
			::= { gps3000p01v1Table 1 }

			Gps3000p01v1Entry ::=
			SEQUENCE {
				gps3000p01v1Index
				ModuleIndex,
				gps3000p01v1Holdover
				Bit0Dis1Ena,
				gps3000p01v1HoldoverTrapEnable
				AlarmEnable,
				gps3000p01v1CableDelay
				DelayX2Ns,
				gps3000p01v1VideoOut
				Bit05251625,
				gps3000p01v1SdiVidHDelay
				DelayPixel1,
				gps3000p01v1SdiVidVDelay
				DelayLines1,
				gps3000p01v1SdiVidFrDelay
				DelayFram1,
				gps3000p01v1AnaVidHDelay
				DelayPixel2,
				gps3000p01v1VitcInsLine
				VideoLine,
				gps3000p01v1AnaVidSch
				Sch1,
				gps3000p01v1HoldoverStat
				Bit0Trk1Hol,
				gps3000p01v1HoldoverStatTrapEnable
				AlarmEnable,
				gps3000p01v1RedundFail
				BitFail,
				gps3000p01v1RedundFailTrapEnable
				AlarmEnable,
				gps3000p01v1OutputsMuted
				BitFail,
				gps3000p01v1OutputsMutedTrapEnable
				AlarmEnable,
				gps3000p01v1SatRxStat
				GpsSatRxStat,
				gps3000p01v1AntenaStat
				GpsAntenaStat,
				gps3000p01v1AntenaStatTrapEnable
				AlarmEnable,
				gps3000p01v1SatNoFail
				BitFail,
				gps3000p01v1AlmanacFail
				BitFail,
				gps3000p01v1GpsModFail
				BitFail,
				gps3000p01v1GpsTrackSats
				GpsSatellites,
				gps3000p01v1GpsVisibleSats
				GpsSatellites,
				gps3000p01v1GpsSignalLevel
				LevelDbHz,
				gps3000p01v1AdquisitionStat
				GpsAdqStat1,
				gps3000p01v1HoldoverTime
				GpsHoldovrTime,
				gps3000p01v1FreqDriftEst
				GpsFrqDrftEst,
				gps3000p01v1PhaseDriftEst
				GpsPhsDrftEst
			 }

		-- 1.3.6.1.4.1.10106.3.101291.1.1.1
		gps3000p01v1Index OBJECT-TYPE
			SYNTAX ModuleIndex
			MAX-ACCESS read-only
			STATUS current
			DESCRIPTION
				"Index of GPS3000P01V1 Table"
		::= { gps3000p01v1Entry 1 }

		-- 1.3.6.1.4.1.10106.3.101291.1.1.3
		gps3000p01v1Holdover OBJECT-TYPE
			SYNTAX Bit0Dis1Ena
			MAX-ACCESS read-write
			STATUS current
			DESCRIPTION
				"Allows setting the module in the holdover mode"
		::= { gps3000p01v1Entry 3 }

		-- 1.3.6.1.4.1.10106.3.101291.1.1.4
		gps3000p01v1HoldoverTrapEnable OBJECT-TYPE
			SYNTAX AlarmEnable
			MAX-ACCESS read-write
			STATUS current
			DESCRIPTION
				"Allows setting the module in the holdover mode Trap Enable"
		::= { gps3000p01v1Entry 4 }

		-- 1.3.6.1.4.1.10106.3.101291.1.1.5
		gps3000p01v1CableDelay OBJECT-TYPE
			SYNTAX DelayX2Ns
			MAX-ACCESS read-write
			STATUS current
			DESCRIPTION
				"Allows compensating the antenna cable delay"
		::= { gps3000p01v1Entry 5 }

		-- 1.3.6.1.4.1.10106.3.101291.1.1.7
		gps3000p01v1VideoOut OBJECT-TYPE
			SYNTAX Bit05251625
			MAX-ACCESS read-only
			STATUS current
			DESCRIPTION
				"Allows selecting the video output format"
		::= { gps3000p01v1Entry 7 }

		-- 1.3.6.1.4.1.10106.3.101291.1.1.9
		gps3000p01v1SdiVidHDelay OBJECT-TYPE
			SYNTAX DelayPixel1
			MAX-ACCESS read-write
			STATUS current
			DESCRIPTION
				"Allows adjusting the SDI video horizontal delay"
		::= { gps3000p01v1Entry 9 }

		-- 1.3.6.1.4.1.10106.3.101291.1.1.11
		gps3000p01v1SdiVidVDelay OBJECT-TYPE
			SYNTAX DelayLines1
			MAX-ACCESS read-write
			STATUS current
			DESCRIPTION
				"Allows adjusting the SDI video vertical delay"
		::= { gps3000p01v1Entry 11 }

		-- 1.3.6.1.4.1.10106.3.101291.1.1.13
		gps3000p01v1SdiVidFrDelay OBJECT-TYPE
			SYNTAX DelayFram1
			MAX-ACCESS read-write
			STATUS current
			DESCRIPTION
				"Allows adjusting the SDI video frame delay"
		::= { gps3000p01v1Entry 13 }

		-- 1.3.6.1.4.1.10106.3.101291.1.1.15
		gps3000p01v1AnaVidHDelay OBJECT-TYPE
			SYNTAX DelayPixel2
			MAX-ACCESS read-write
			STATUS current
			DESCRIPTION
				"Allows adjusting the Analog to SDI video horizontal delay"
		::= { gps3000p01v1Entry 15 }

		-- 1.3.6.1.4.1.10106.3.101291.1.1.17
		gps3000p01v1VitcInsLine OBJECT-TYPE
			SYNTAX VideoLine
			MAX-ACCESS read-write
			STATUS current
			DESCRIPTION
				"Allows adjusting the VITC insertion line"
		::= { gps3000p01v1Entry 17 }

		-- 1.3.6.1.4.1.10106.3.101291.1.1.19
		gps3000p01v1AnaVidSch OBJECT-TYPE
			SYNTAX Sch1
			MAX-ACCESS read-write
			STATUS current
			DESCRIPTION
				"Allows adjusting the Analog video SCH"
		::= { gps3000p01v1Entry 19 }

		-- 1.3.6.1.4.1.10106.3.101291.1.1.21
		gps3000p01v1HoldoverStat OBJECT-TYPE
			SYNTAX Bit0Trk1Hol
			MAX-ACCESS read-only
			STATUS current
			DESCRIPTION
				"Indicates if the module is locked to GPS or to reference or it is in holdover mode"
		::= { gps3000p01v1Entry 21 }

		-- 1.3.6.1.4.1.10106.3.101291.1.1.22
		gps3000p01v1HoldoverStatTrapEnable OBJECT-TYPE
			SYNTAX AlarmEnable
			MAX-ACCESS read-write
			STATUS current
			DESCRIPTION
				"Indicates if the module is locked to GPS or to reference or it is in holdover mode Trap Enable"
		::= { gps3000p01v1Entry 22 }

		-- 1.3.6.1.4.1.10106.3.101291.1.1.23
		gps3000p01v1RedundFail OBJECT-TYPE
			SYNTAX BitFail
			MAX-ACCESS read-only
			STATUS current
			DESCRIPTION
				"Indicates if there is any active module in the redundance system"
		::= { gps3000p01v1Entry 23 }

		-- 1.3.6.1.4.1.10106.3.101291.1.1.24
		gps3000p01v1RedundFailTrapEnable OBJECT-TYPE
			SYNTAX AlarmEnable
			MAX-ACCESS read-write
			STATUS current
			DESCRIPTION
				"Indicates if there is any active module in the redundance system Trap Enable"
		::= { gps3000p01v1Entry 24 }

		-- 1.3.6.1.4.1.10106.3.101291.1.1.25
		gps3000p01v1OutputsMuted OBJECT-TYPE
			SYNTAX BitFail
			MAX-ACCESS read-only
			STATUS current
			DESCRIPTION
				"Indicates f the module outputs are active"
		::= { gps3000p01v1Entry 25 }

		-- 1.3.6.1.4.1.10106.3.101291.1.1.26
		gps3000p01v1OutputsMutedTrapEnable OBJECT-TYPE
			SYNTAX AlarmEnable
			MAX-ACCESS read-write
			STATUS current
			DESCRIPTION
				"Indicates f the module outputs are active Trap Enable"
		::= { gps3000p01v1Entry 26 }

		-- 1.3.6.1.4.1.10106.3.101291.1.1.27
		gps3000p01v1SatRxStat OBJECT-TYPE
			SYNTAX GpsSatRxStat
			MAX-ACCESS read-only
			STATUS current
			DESCRIPTION
				"GPS receiver module satellite tracking status"
		::= { gps3000p01v1Entry 27 }

		-- 1.3.6.1.4.1.10106.3.101291.1.1.29
		gps3000p01v1AntenaStat OBJECT-TYPE
			SYNTAX GpsAntenaStat
			MAX-ACCESS read-only
			STATUS current
			DESCRIPTION
				"Antenna connection status"
		::= { gps3000p01v1Entry 29 }

		-- 1.3.6.1.4.1.10106.3.101291.1.1.30
		gps3000p01v1AntenaStatTrapEnable OBJECT-TYPE
			SYNTAX AlarmEnable
			MAX-ACCESS read-write
			STATUS current
			DESCRIPTION
				"Antenna connection status Trap Enable"
		::= { gps3000p01v1Entry 30 }

		-- 1.3.6.1.4.1.10106.3.101291.1.1.31
		gps3000p01v1SatNoFail OBJECT-TYPE
			SYNTAX BitFail
			MAX-ACCESS read-only
			STATUS current
			DESCRIPTION
				"Indicates that the number of visible satellites is low"
		::= { gps3000p01v1Entry 31 }

		-- 1.3.6.1.4.1.10106.3.101291.1.1.33
		gps3000p01v1AlmanacFail OBJECT-TYPE
			SYNTAX BitFail
			MAX-ACCESS read-only
			STATUS current
			DESCRIPTION
				"Indicates that the modules has an invalid almanac"
		::= { gps3000p01v1Entry 33 }

		-- 1.3.6.1.4.1.10106.3.101291.1.1.35
		gps3000p01v1GpsModFail OBJECT-TYPE
			SYNTAX BitFail
			MAX-ACCESS read-only
			STATUS current
			DESCRIPTION
				"Indicates that an error has been detected in the GPS receiver module"
		::= { gps3000p01v1Entry 35 }

		-- 1.3.6.1.4.1.10106.3.101291.1.1.37
		gps3000p01v1GpsTrackSats OBJECT-TYPE
			SYNTAX GpsSatellites
			MAX-ACCESS read-only
			STATUS current
			DESCRIPTION
				"Number of GPS tracking satellites"
		::= { gps3000p01v1Entry 37 }

		-- 1.3.6.1.4.1.10106.3.101291.1.1.39
		gps3000p01v1GpsVisibleSats OBJECT-TYPE
			SYNTAX GpsSatellites
			MAX-ACCESS read-only
			STATUS current
			DESCRIPTION
				"Number of GPS visible satellites"
		::= { gps3000p01v1Entry 39 }

		-- 1.3.6.1.4.1.10106.3.101291.1.1.41
		gps3000p01v1GpsSignalLevel OBJECT-TYPE
			SYNTAX LevelDbHz
			MAX-ACCESS read-only
			STATUS current
			DESCRIPTION
				"Estimated carrier to noise ratio for the best satellite in tracking"
		::= { gps3000p01v1Entry 41 }

		-- 1.3.6.1.4.1.10106.3.101291.1.1.43
		gps3000p01v1AdquisitionStat OBJECT-TYPE
			SYNTAX GpsAdqStat1
			MAX-ACCESS read-only
			STATUS current
			DESCRIPTION
				"GPS3000 module adquisition status"
		::= { gps3000p01v1Entry 43 }

		-- 1.3.6.1.4.1.10106.3.101291.1.1.45
		gps3000p01v1HoldoverTime OBJECT-TYPE
			SYNTAX GpsHoldovrTime
			MAX-ACCESS read-only
			STATUS current
			DESCRIPTION
				"Holdover time"
		::= { gps3000p01v1Entry 45 }

		-- 1.3.6.1.4.1.10106.3.101291.1.1.47
		gps3000p01v1FreqDriftEst OBJECT-TYPE
			SYNTAX GpsFrqDrftEst
			MAX-ACCESS read-only
			STATUS current
			DESCRIPTION
				"Frequency drift estimation"
		::= { gps3000p01v1Entry 47 }

		-- 1.3.6.1.4.1.10106.3.101291.1.1.49
		gps3000p01v1PhaseDriftEst OBJECT-TYPE
			SYNTAX GpsPhsDrftEst
			MAX-ACCESS read-only
			STATUS current
			DESCRIPTION
				"Phase drift estimation"
		::= { gps3000p01v1Entry 49 }

		-- 1.3.6.1.4.1.10106.3.195702
		gps3000p01v2 OBJECT IDENTIFIER ::= { albalaProducts 195702 }

		-- 1.3.6.1.4.1.10106.3.195702.1
		gps3000p01v2Table  OBJECT-TYPE
			SYNTAX SEQUENCE OF Gps3000p01v2Entry
			MAX-ACCESS not-accessible
			STATUS current
			DESCRIPTION
				"Module  GPS3000P01V2 Table"
			::= { gps3000p01v2 1 }

		-- 1.3.6.1.4.1.10106.3.195702.1.1
		gps3000p01v2Entry  OBJECT-TYPE
			SYNTAX Gps3000p01v2Entry
			MAX-ACCESS not-accessible
			STATUS current
			DESCRIPTION
				"Module GPS3000P01V2 Entry"
			INDEX { gps3000p01v2Index }
			::= { gps3000p01v2Table 1 }

			Gps3000p01v2Entry ::=
			SEQUENCE {
				gps3000p01v2Index
				ModuleIndex,
				gps3000p01v2Holdover
				Bit0Dis1Ena,
				gps3000p01v2HoldoverTrapEnable
				AlarmEnable,
				gps3000p01v2CableDelay
				DelayX2Ns,
				gps3000p01v2VideoOut
				Bit05251625,
				gps3000p01v2SdiVidHDelay
				DelayPixel1,
				gps3000p01v2SdiVidVDelay
				DelayLines1,
				gps3000p01v2SdiVidFrDelay
				DelayFram1,
				gps3000p01v2AnaVidHDelay
				DelayPixel2,
				gps3000p01v2VitcInsLine
				VideoLine,
				gps3000p01v2AnaVidSch
				Sch1,
				gps3000p01v2HoldoverStat
				Bit0Trk1Hol,
				gps3000p01v2HoldoverStatTrapEnable
				AlarmEnable,
				gps3000p01v2RedundFail
				BitFail,
				gps3000p01v2RedundFailTrapEnable
				AlarmEnable,
				gps3000p01v2OutputsMuted
				BitFail,
				gps3000p01v2OutputsMutedTrapEnable
				AlarmEnable,
				gps3000p01v2SatRxStat
				GpsSatRxStat,
				gps3000p01v2AntenaStat
				GpsAntenaStat,
				gps3000p01v2AntenaStatTrapEnable
				AlarmEnable,
				gps3000p01v2SatNoFail
				BitFail,
				gps3000p01v2AlmanacFail
				BitFail,
				gps3000p01v2GpsModFail
				BitFail,
				gps3000p01v2GpsTrackSats
				GpsSatellites,
				gps3000p01v2GpsVisibleSats
				GpsSatellites,
				gps3000p01v2GpsSignalLevel
				LevelDbHz,
				gps3000p01v2AdquisitionStat
				GpsAdqStat1,
				gps3000p01v2HoldoverTime
				GpsHoldovrTime,
				gps3000p01v2FreqDriftEst
				GpsFrqDrftEst,
				gps3000p01v2PhaseDriftEst
				GpsPhsDrftEst
			 }

		-- 1.3.6.1.4.1.10106.3.101291.1.1.1
		gps3000p01v2Index OBJECT-TYPE
			SYNTAX ModuleIndex
			MAX-ACCESS read-only
			STATUS current
			DESCRIPTION
				"Index of GPS3000P01V2 Table"
		::= { gps3000p01v2Entry 1 }

		-- 1.3.6.1.4.1.10106.3.101291.1.1.3
		gps3000p01v2Holdover OBJECT-TYPE
			SYNTAX Bit0Dis1Ena
			MAX-ACCESS read-write
			STATUS current
			DESCRIPTION
				"Allows setting the module in the holdover mode"
		::= { gps3000p01v2Entry 3 }

		-- 1.3.6.1.4.1.10106.3.101291.1.1.4
		gps3000p01v2HoldoverTrapEnable OBJECT-TYPE
			SYNTAX AlarmEnable
			MAX-ACCESS read-write
			STATUS current
			DESCRIPTION
				"Allows setting the module in the holdover mode Trap Enable"
		::= { gps3000p01v2Entry 4 }

		-- 1.3.6.1.4.1.10106.3.101291.1.1.5
		gps3000p01v2CableDelay OBJECT-TYPE
			SYNTAX DelayX2Ns
			MAX-ACCESS read-write
			STATUS current
			DESCRIPTION
				"Allows compensating the antenna cable delay"
		::= { gps3000p01v2Entry 5 }

		-- 1.3.6.1.4.1.10106.3.101291.1.1.7
		gps3000p01v2VideoOut OBJECT-TYPE
			SYNTAX Bit05251625
			MAX-ACCESS read-only
			STATUS current
			DESCRIPTION
				"Allows selecting the video output format"
		::= { gps3000p01v2Entry 7 }

		-- 1.3.6.1.4.1.10106.3.101291.1.1.9
		gps3000p01v2SdiVidHDelay OBJECT-TYPE
			SYNTAX DelayPixel1
			MAX-ACCESS read-write
			STATUS current
			DESCRIPTION
				"Allows adjusting the SDI video horizontal delay"
		::= { gps3000p01v2Entry 9 }

		-- 1.3.6.1.4.1.10106.3.101291.1.1.11
		gps3000p01v2SdiVidVDelay OBJECT-TYPE
			SYNTAX DelayLines1
			MAX-ACCESS read-write
			STATUS current
			DESCRIPTION
				"Allows adjusting the SDI video vertical delay"
		::= { gps3000p01v2Entry 11 }

		-- 1.3.6.1.4.1.10106.3.101291.1.1.13
		gps3000p01v2SdiVidFrDelay OBJECT-TYPE
			SYNTAX DelayFram1
			MAX-ACCESS read-write
			STATUS current
			DESCRIPTION
				"Allows adjusting the SDI video frame delay"
		::= { gps3000p01v2Entry 13 }

		-- 1.3.6.1.4.1.10106.3.101291.1.1.15
		gps3000p01v2AnaVidHDelay OBJECT-TYPE
			SYNTAX DelayPixel2
			MAX-ACCESS read-write
			STATUS current
			DESCRIPTION
				"Allows adjusting the Analog to SDI video horizontal delay"
		::= { gps3000p01v2Entry 15 }

		-- 1.3.6.1.4.1.10106.3.101291.1.1.17
		gps3000p01v2VitcInsLine OBJECT-TYPE
			SYNTAX VideoLine
			MAX-ACCESS read-write
			STATUS current
			DESCRIPTION
				"Allows adjusting the VITC insertion line"
		::= { gps3000p01v2Entry 17 }

		-- 1.3.6.1.4.1.10106.3.101291.1.1.19
		gps3000p01v2AnaVidSch OBJECT-TYPE
			SYNTAX Sch1
			MAX-ACCESS read-write
			STATUS current
			DESCRIPTION
				"Allows adjusting the Analog video SCH"
		::= { gps3000p01v2Entry 19 }

		-- 1.3.6.1.4.1.10106.3.101291.1.1.21
		gps3000p01v2HoldoverStat OBJECT-TYPE
			SYNTAX Bit0Trk1Hol
			MAX-ACCESS read-only
			STATUS current
			DESCRIPTION
				"Indicates if the module is locked to GPS or to reference or it is in holdover mode"
		::= { gps3000p01v2Entry 21 }

		-- 1.3.6.1.4.1.10106.3.101291.1.1.22
		gps3000p01v2HoldoverStatTrapEnable OBJECT-TYPE
			SYNTAX AlarmEnable
			MAX-ACCESS read-write
			STATUS current
			DESCRIPTION
				"Indicates if the module is locked to GPS or to reference or it is in holdover mode Trap Enable"
		::= { gps3000p01v2Entry 22 }

		-- 1.3.6.1.4.1.10106.3.101291.1.1.23
		gps3000p01v2RedundFail OBJECT-TYPE
			SYNTAX BitFail
			MAX-ACCESS read-only
			STATUS current
			DESCRIPTION
				"Indicates if there is any active module in the redundance system"
		::= { gps3000p01v2Entry 23 }

		-- 1.3.6.1.4.1.10106.3.101291.1.1.24
		gps3000p01v2RedundFailTrapEnable OBJECT-TYPE
			SYNTAX AlarmEnable
			MAX-ACCESS read-write
			STATUS current
			DESCRIPTION
				"Indicates if there is any active module in the redundance system Trap Enable"
		::= { gps3000p01v2Entry 24 }

		-- 1.3.6.1.4.1.10106.3.101291.1.1.25
		gps3000p01v2OutputsMuted OBJECT-TYPE
			SYNTAX BitFail
			MAX-ACCESS read-only
			STATUS current
			DESCRIPTION
				"Indicates f the module outputs are active"
		::= { gps3000p01v2Entry 25 }

		-- 1.3.6.1.4.1.10106.3.101291.1.1.26
		gps3000p01v2OutputsMutedTrapEnable OBJECT-TYPE
			SYNTAX AlarmEnable
			MAX-ACCESS read-write
			STATUS current
			DESCRIPTION
				"Indicates f the module outputs are active Trap Enable"
		::= { gps3000p01v2Entry 26 }

		-- 1.3.6.1.4.1.10106.3.101291.1.1.27
		gps3000p01v2SatRxStat OBJECT-TYPE
			SYNTAX GpsSatRxStat
			MAX-ACCESS read-only
			STATUS current
			DESCRIPTION
				"GPS receiver module satellite tracking status"
		::= { gps3000p01v2Entry 27 }

		-- 1.3.6.1.4.1.10106.3.101291.1.1.29
		gps3000p01v2AntenaStat OBJECT-TYPE
			SYNTAX GpsAntenaStat
			MAX-ACCESS read-only
			STATUS current
			DESCRIPTION
				"Antenna connection status"
		::= { gps3000p01v2Entry 29 }

		-- 1.3.6.1.4.1.10106.3.101291.1.1.30
		gps3000p01v2AntenaStatTrapEnable OBJECT-TYPE
			SYNTAX AlarmEnable
			MAX-ACCESS read-write
			STATUS current
			DESCRIPTION
				"Antenna connection status Trap Enable"
		::= { gps3000p01v2Entry 30 }

		-- 1.3.6.1.4.1.10106.3.101291.1.1.31
		gps3000p01v2SatNoFail OBJECT-TYPE
			SYNTAX BitFail
			MAX-ACCESS read-only
			STATUS current
			DESCRIPTION
				"Indicates that the number of visible satellites is low"
		::= { gps3000p01v2Entry 31 }

		-- 1.3.6.1.4.1.10106.3.101291.1.1.33
		gps3000p01v2AlmanacFail OBJECT-TYPE
			SYNTAX BitFail
			MAX-ACCESS read-only
			STATUS current
			DESCRIPTION
				"Indicates that the modules has an invalid almanac"
		::= { gps3000p01v2Entry 33 }

		-- 1.3.6.1.4.1.10106.3.101291.1.1.35
		gps3000p01v2GpsModFail OBJECT-TYPE
			SYNTAX BitFail
			MAX-ACCESS read-only
			STATUS current
			DESCRIPTION
				"Indicates that an error has been detected in the GPS receiver module"
		::= { gps3000p01v2Entry 35 }

		-- 1.3.6.1.4.1.10106.3.101291.1.1.37
		gps3000p01v2GpsTrackSats OBJECT-TYPE
			SYNTAX GpsSatellites
			MAX-ACCESS read-only
			STATUS current
			DESCRIPTION
				"Number of GPS tracking satellites"
		::= { gps3000p01v2Entry 37 }

		-- 1.3.6.1.4.1.10106.3.101291.1.1.39
		gps3000p01v2GpsVisibleSats OBJECT-TYPE
			SYNTAX GpsSatellites
			MAX-ACCESS read-only
			STATUS current
			DESCRIPTION
				"Number of GPS visible satellites"
		::= { gps3000p01v2Entry 39 }

		-- 1.3.6.1.4.1.10106.3.101291.1.1.41
		gps3000p01v2GpsSignalLevel OBJECT-TYPE
			SYNTAX LevelDbHz
			MAX-ACCESS read-only
			STATUS current
			DESCRIPTION
				"Estimated carrier to noise ratio for the best satellite in tracking"
		::= { gps3000p01v2Entry 41 }

		-- 1.3.6.1.4.1.10106.3.101291.1.1.43
		gps3000p01v2AdquisitionStat OBJECT-TYPE
			SYNTAX GpsAdqStat1
			MAX-ACCESS read-only
			STATUS current
			DESCRIPTION
				"GPS3000 module adquisition status"
		::= { gps3000p01v2Entry 43 }

		-- 1.3.6.1.4.1.10106.3.101291.1.1.45
		gps3000p01v2HoldoverTime OBJECT-TYPE
			SYNTAX GpsHoldovrTime
			MAX-ACCESS read-only
			STATUS current
			DESCRIPTION
				"Holdover time"
		::= { gps3000p01v2Entry 45 }

		-- 1.3.6.1.4.1.10106.3.101291.1.1.47
		gps3000p01v2FreqDriftEst OBJECT-TYPE
			SYNTAX GpsFrqDrftEst
			MAX-ACCESS read-only
			STATUS current
			DESCRIPTION
				"Frequency drift estimation"
		::= { gps3000p01v2Entry 47 }

		-- 1.3.6.1.4.1.10106.3.101291.1.1.49
		gps3000p01v2PhaseDriftEst OBJECT-TYPE
			SYNTAX GpsPhsDrftEst
			MAX-ACCESS read-only
			STATUS current
			DESCRIPTION
				"Phase drift estimation"
		::= { gps3000p01v2Entry 49 }

		-- 1.3.6.1.4.1.10106.3.195703
		gps3000p01v3 OBJECT IDENTIFIER ::= { albalaProducts 195703 }

		-- 1.3.6.1.4.1.10106.3.195703.1
		gps3000p01v3Table  OBJECT-TYPE
			SYNTAX SEQUENCE OF Gps3000p01v3Entry
			MAX-ACCESS not-accessible
			STATUS current
			DESCRIPTION
				"Module  GPS3000P01V3 Table"
			::= { gps3000p01v3 1 }

		-- 1.3.6.1.4.1.10106.3.195703.1.1
		gps3000p01v3Entry  OBJECT-TYPE
			SYNTAX Gps3000p01v3Entry
			MAX-ACCESS not-accessible
			STATUS current
			DESCRIPTION
				"Module GPS3000P01V3 Entry"
			INDEX { gps3000p01v3Index }
			::= { gps3000p01v3Table 1 }

			Gps3000p01v3Entry ::=
			SEQUENCE {
				gps3000p01v3Index
				ModuleIndex,
				gps3000p01v3Holdover
				Bit0Dis1Ena,
				gps3000p01v3HoldoverTrapEnable
				AlarmEnable,
				gps3000p01v3CableDelay
				DelayX2Ns,
				gps3000p01v3VideoOut
				Bit05251625,
				gps3000p01v3SdiVidHDelay
				DelayPixel1,
				gps3000p01v3SdiVidVDelay
				DelayLines1,
				gps3000p01v3SdiVidFrDelay
				DelayFram1,
				gps3000p01v3AnaVidHDelay
				DelayPixel2,
				gps3000p01v3VitcInsLine
				VideoLine,
				gps3000p01v3AnaVidSch
				Sch1,
				gps3000p01v3HoldoverStat
				Bit0Trk1Hol,
				gps3000p01v3HoldoverStatTrapEnable
				AlarmEnable,
				gps3000p01v3RedundFail
				BitFail,
				gps3000p01v3RedundFailTrapEnable
				AlarmEnable,
				gps3000p01v3OutputsMuted
				BitFail,
				gps3000p01v3OutputsMutedTrapEnable
				AlarmEnable,
				gps3000p01v3SatRxStat
				GpsSatRxStat,
				gps3000p01v3AntenaStat
				GpsAntenaStat,
				gps3000p01v3AntenaStatTrapEnable
				AlarmEnable,
				gps3000p01v3SatNoFail
				BitFail,
				gps3000p01v3AlmanacFail
				BitFail,
				gps3000p01v3GpsModFail
				BitFail,
				gps3000p01v3GpsTrackSats
				GpsSatellites,
				gps3000p01v3GpsVisibleSats
				GpsSatellites,
				gps3000p01v3GpsSignalLevel
				LevelDbHz,
				gps3000p01v3AdquisitionStat
				GpsAdqStat1,
				gps3000p01v3HoldoverTime
				GpsHoldovrTime,
				gps3000p01v3FreqDriftEst
				GpsFrqDrftEst,
				gps3000p01v3PhaseDriftEst
				GpsPhsDrftEst
			 }

		-- 1.3.6.1.4.1.10106.3.101291.1.1.1
		gps3000p01v3Index OBJECT-TYPE
			SYNTAX ModuleIndex
			MAX-ACCESS read-only
			STATUS current
			DESCRIPTION
				"Index of GPS3000P01V3 Table"
		::= { gps3000p01v3Entry 1 }

		-- 1.3.6.1.4.1.10106.3.101291.1.1.3
		gps3000p01v3Holdover OBJECT-TYPE
			SYNTAX Bit0Dis1Ena
			MAX-ACCESS read-write
			STATUS current
			DESCRIPTION
				"Allows setting the module in the holdover mode"
		::= { gps3000p01v3Entry 3 }

		-- 1.3.6.1.4.1.10106.3.101291.1.1.4
		gps3000p01v3HoldoverTrapEnable OBJECT-TYPE
			SYNTAX AlarmEnable
			MAX-ACCESS read-write
			STATUS current
			DESCRIPTION
				"Allows setting the module in the holdover mode Trap Enable"
		::= { gps3000p01v3Entry 4 }

		-- 1.3.6.1.4.1.10106.3.101291.1.1.5
		gps3000p01v3CableDelay OBJECT-TYPE
			SYNTAX DelayX2Ns
			MAX-ACCESS read-write
			STATUS current
			DESCRIPTION
				"Allows compensating the antenna cable delay"
		::= { gps3000p01v3Entry 5 }

		-- 1.3.6.1.4.1.10106.3.101291.1.1.7
		gps3000p01v3VideoOut OBJECT-TYPE
			SYNTAX Bit05251625
			MAX-ACCESS read-only
			STATUS current
			DESCRIPTION
				"Allows selecting the video output format"
		::= { gps3000p01v3Entry 7 }

		-- 1.3.6.1.4.1.10106.3.101291.1.1.9
		gps3000p01v3SdiVidHDelay OBJECT-TYPE
			SYNTAX DelayPixel1
			MAX-ACCESS read-write
			STATUS current
			DESCRIPTION
				"Allows adjusting the SDI video horizontal delay"
		::= { gps3000p01v3Entry 9 }

		-- 1.3.6.1.4.1.10106.3.101291.1.1.11
		gps3000p01v3SdiVidVDelay OBJECT-TYPE
			SYNTAX DelayLines1
			MAX-ACCESS read-write
			STATUS current
			DESCRIPTION
				"Allows adjusting the SDI video vertical delay"
		::= { gps3000p01v3Entry 11 }

		-- 1.3.6.1.4.1.10106.3.101291.1.1.13
		gps3000p01v3SdiVidFrDelay OBJECT-TYPE
			SYNTAX DelayFram1
			MAX-ACCESS read-write
			STATUS current
			DESCRIPTION
				"Allows adjusting the SDI video frame delay"
		::= { gps3000p01v3Entry 13 }

		-- 1.3.6.1.4.1.10106.3.101291.1.1.15
		gps3000p01v3AnaVidHDelay OBJECT-TYPE
			SYNTAX DelayPixel2
			MAX-ACCESS read-write
			STATUS current
			DESCRIPTION
				"Allows adjusting the Analog to SDI video horizontal delay"
		::= { gps3000p01v3Entry 15 }

		-- 1.3.6.1.4.1.10106.3.101291.1.1.17
		gps3000p01v3VitcInsLine OBJECT-TYPE
			SYNTAX VideoLine
			MAX-ACCESS read-write
			STATUS current
			DESCRIPTION
				"Allows adjusting the VITC insertion line"
		::= { gps3000p01v3Entry 17 }

		-- 1.3.6.1.4.1.10106.3.101291.1.1.19
		gps3000p01v3AnaVidSch OBJECT-TYPE
			SYNTAX Sch1
			MAX-ACCESS read-write
			STATUS current
			DESCRIPTION
				"Allows adjusting the Analog video SCH"
		::= { gps3000p01v3Entry 19 }

		-- 1.3.6.1.4.1.10106.3.101291.1.1.21
		gps3000p01v3HoldoverStat OBJECT-TYPE
			SYNTAX Bit0Trk1Hol
			MAX-ACCESS read-only
			STATUS current
			DESCRIPTION
				"Indicates if the module is locked to GPS or to reference or it is in holdover mode"
		::= { gps3000p01v3Entry 21 }

		-- 1.3.6.1.4.1.10106.3.101291.1.1.22
		gps3000p01v3HoldoverStatTrapEnable OBJECT-TYPE
			SYNTAX AlarmEnable
			MAX-ACCESS read-write
			STATUS current
			DESCRIPTION
				"Indicates if the module is locked to GPS or to reference or it is in holdover mode Trap Enable"
		::= { gps3000p01v3Entry 22 }

		-- 1.3.6.1.4.1.10106.3.101291.1.1.23
		gps3000p01v3RedundFail OBJECT-TYPE
			SYNTAX BitFail
			MAX-ACCESS read-only
			STATUS current
			DESCRIPTION
				"Indicates if there is any active module in the redundance system"
		::= { gps3000p01v3Entry 23 }

		-- 1.3.6.1.4.1.10106.3.101291.1.1.24
		gps3000p01v3RedundFailTrapEnable OBJECT-TYPE
			SYNTAX AlarmEnable
			MAX-ACCESS read-write
			STATUS current
			DESCRIPTION
				"Indicates if there is any active module in the redundance system Trap Enable"
		::= { gps3000p01v3Entry 24 }

		-- 1.3.6.1.4.1.10106.3.101291.1.1.25
		gps3000p01v3OutputsMuted OBJECT-TYPE
			SYNTAX BitFail
			MAX-ACCESS read-only
			STATUS current
			DESCRIPTION
				"Indicates f the module outputs are active"
		::= { gps3000p01v3Entry 25 }

		-- 1.3.6.1.4.1.10106.3.101291.1.1.26
		gps3000p01v3OutputsMutedTrapEnable OBJECT-TYPE
			SYNTAX AlarmEnable
			MAX-ACCESS read-write
			STATUS current
			DESCRIPTION
				"Indicates f the module outputs are active Trap Enable"
		::= { gps3000p01v3Entry 26 }

		-- 1.3.6.1.4.1.10106.3.101291.1.1.27
		gps3000p01v3SatRxStat OBJECT-TYPE
			SYNTAX GpsSatRxStat
			MAX-ACCESS read-only
			STATUS current
			DESCRIPTION
				"GPS receiver module satellite tracking status"
		::= { gps3000p01v3Entry 27 }

		-- 1.3.6.1.4.1.10106.3.101291.1.1.29
		gps3000p01v3AntenaStat OBJECT-TYPE
			SYNTAX GpsAntenaStat
			MAX-ACCESS read-only
			STATUS current
			DESCRIPTION
				"Antenna connection status"
		::= { gps3000p01v3Entry 29 }

		-- 1.3.6.1.4.1.10106.3.101291.1.1.30
		gps3000p01v3AntenaStatTrapEnable OBJECT-TYPE
			SYNTAX AlarmEnable
			MAX-ACCESS read-write
			STATUS current
			DESCRIPTION
				"Antenna connection status Trap Enable"
		::= { gps3000p01v3Entry 30 }

		-- 1.3.6.1.4.1.10106.3.101291.1.1.31
		gps3000p01v3SatNoFail OBJECT-TYPE
			SYNTAX BitFail
			MAX-ACCESS read-only
			STATUS current
			DESCRIPTION
				"Indicates that the number of visible satellites is low"
		::= { gps3000p01v3Entry 31 }

		-- 1.3.6.1.4.1.10106.3.101291.1.1.33
		gps3000p01v3AlmanacFail OBJECT-TYPE
			SYNTAX BitFail
			MAX-ACCESS read-only
			STATUS current
			DESCRIPTION
				"Indicates that the modules has an invalid almanac"
		::= { gps3000p01v3Entry 33 }

		-- 1.3.6.1.4.1.10106.3.101291.1.1.35
		gps3000p01v3GpsModFail OBJECT-TYPE
			SYNTAX BitFail
			MAX-ACCESS read-only
			STATUS current
			DESCRIPTION
				"Indicates that an error has been detected in the GPS receiver module"
		::= { gps3000p01v3Entry 35 }

		-- 1.3.6.1.4.1.10106.3.101291.1.1.37
		gps3000p01v3GpsTrackSats OBJECT-TYPE
			SYNTAX GpsSatellites
			MAX-ACCESS read-only
			STATUS current
			DESCRIPTION
				"Number of GPS tracking satellites"
		::= { gps3000p01v3Entry 37 }

		-- 1.3.6.1.4.1.10106.3.101291.1.1.39
		gps3000p01v3GpsVisibleSats OBJECT-TYPE
			SYNTAX GpsSatellites
			MAX-ACCESS read-only
			STATUS current
			DESCRIPTION
				"Number of GPS visible satellites"
		::= { gps3000p01v3Entry 39 }

		-- 1.3.6.1.4.1.10106.3.101291.1.1.41
		gps3000p01v3GpsSignalLevel OBJECT-TYPE
			SYNTAX LevelDbHz
			MAX-ACCESS read-only
			STATUS current
			DESCRIPTION
				"Estimated carrier to noise ratio for the best satellite in tracking"
		::= { gps3000p01v3Entry 41 }

		-- 1.3.6.1.4.1.10106.3.101291.1.1.43
		gps3000p01v3AdquisitionStat OBJECT-TYPE
			SYNTAX GpsAdqStat1
			MAX-ACCESS read-only
			STATUS current
			DESCRIPTION
				"GPS3000 module adquisition status"
		::= { gps3000p01v3Entry 43 }

		-- 1.3.6.1.4.1.10106.3.101291.1.1.45
		gps3000p01v3HoldoverTime OBJECT-TYPE
			SYNTAX GpsHoldovrTime
			MAX-ACCESS read-only
			STATUS current
			DESCRIPTION
				"Holdover time"
		::= { gps3000p01v3Entry 45 }

		-- 1.3.6.1.4.1.10106.3.101291.1.1.47
		gps3000p01v3FreqDriftEst OBJECT-TYPE
			SYNTAX GpsFrqDrftEst
			MAX-ACCESS read-only
			STATUS current
			DESCRIPTION
				"Frequency drift estimation"
		::= { gps3000p01v3Entry 47 }

		-- 1.3.6.1.4.1.10106.3.101291.1.1.49
		gps3000p01v3PhaseDriftEst OBJECT-TYPE
			SYNTAX GpsPhsDrftEst
			MAX-ACCESS read-only
			STATUS current
			DESCRIPTION
				"Phase drift estimation"
		::= { gps3000p01v3Entry 49 }

		-- 1.3.6.1.4.1.10106.3.195704
		gps3000p01v4 OBJECT IDENTIFIER ::= { albalaProducts 195704 }

		-- 1.3.6.1.4.1.10106.3.195704.1
		gps3000p01v4Table  OBJECT-TYPE
			SYNTAX SEQUENCE OF Gps3000p01v4Entry
			MAX-ACCESS not-accessible
			STATUS current
			DESCRIPTION
				"Module  GPS3000P01V4 Table"
			::= { gps3000p01v4 1 }

		-- 1.3.6.1.4.1.10106.3.195704.1.1
		gps3000p01v4Entry  OBJECT-TYPE
			SYNTAX Gps3000p01v4Entry
			MAX-ACCESS not-accessible
			STATUS current
			DESCRIPTION
				"Module GPS3000P01V4 Entry"
			INDEX { gps3000p01v4Index }
			::= { gps3000p01v4Table 1 }

			Gps3000p01v4Entry ::=
			SEQUENCE {
				gps3000p01v4Index
				ModuleIndex,
				gps3000p01v4Holdover
				Bit0Dis1Ena,
				gps3000p01v4HoldoverTrapEnable
				AlarmEnable,
				gps3000p01v4CableDelay
				DelayX2Ns,
				gps3000p01v4VideoOut
				Bit05251625,
				gps3000p01v4SdiVidHDelay
				DelayPixel1,
				gps3000p01v4SdiVidVDelay
				DelayLines1,
				gps3000p01v4SdiVidFrDelay
				DelayFram1,
				gps3000p01v4AnaVidHDelay
				DelayPixel2,
				gps3000p01v4VitcInsLine
				VideoLine,
				gps3000p01v4AnaVidSch
				Sch1,
				gps3000p01v4HoldoverStat
				Bit0Trk1Hol,
				gps3000p01v4HoldoverStatTrapEnable
				AlarmEnable,
				gps3000p01v4RedundFail
				BitFail,
				gps3000p01v4RedundFailTrapEnable
				AlarmEnable,
				gps3000p01v4OutputsMuted
				BitFail,
				gps3000p01v4OutputsMutedTrapEnable
				AlarmEnable,
				gps3000p01v4SatRxStat
				GpsSatRxStat,
				gps3000p01v4AntenaStat
				GpsAntenaStat,
				gps3000p01v4AntenaStatTrapEnable
				AlarmEnable,
				gps3000p01v4SatNoFail
				BitFail,
				gps3000p01v4AlmanacFail
				BitFail,
				gps3000p01v4GpsModFail
				BitFail,
				gps3000p01v4GpsTrackSats
				GpsSatellites,
				gps3000p01v4GpsVisibleSats
				GpsSatellites,
				gps3000p01v4GpsSignalLevel
				LevelDbHz,
				gps3000p01v4AdquisitionStat
				GpsAdqStat1,
				gps3000p01v4HoldoverTime
				GpsHoldovrTime,
				gps3000p01v4FreqDriftEst
				GpsFrqDrftEst,
				gps3000p01v4PhaseDriftEst
				GpsPhsDrftEst
			 }

		-- 1.3.6.1.4.1.10106.3.101291.1.1.1
		gps3000p01v4Index OBJECT-TYPE
			SYNTAX ModuleIndex
			MAX-ACCESS read-only
			STATUS current
			DESCRIPTION
				"Index of GPS3000P01V4 Table"
		::= { gps3000p01v4Entry 1 }

		-- 1.3.6.1.4.1.10106.3.101291.1.1.3
		gps3000p01v4Holdover OBJECT-TYPE
			SYNTAX Bit0Dis1Ena
			MAX-ACCESS read-write
			STATUS current
			DESCRIPTION
				"Allows setting the module in the holdover mode"
		::= { gps3000p01v4Entry 3 }

		-- 1.3.6.1.4.1.10106.3.101291.1.1.4
		gps3000p01v4HoldoverTrapEnable OBJECT-TYPE
			SYNTAX AlarmEnable
			MAX-ACCESS read-write
			STATUS current
			DESCRIPTION
				"Allows setting the module in the holdover mode Trap Enable"
		::= { gps3000p01v4Entry 4 }

		-- 1.3.6.1.4.1.10106.3.101291.1.1.5
		gps3000p01v4CableDelay OBJECT-TYPE
			SYNTAX DelayX2Ns
			MAX-ACCESS read-write
			STATUS current
			DESCRIPTION
				"Allows compensating the antenna cable delay"
		::= { gps3000p01v4Entry 5 }

		-- 1.3.6.1.4.1.10106.3.101291.1.1.7
		gps3000p01v4VideoOut OBJECT-TYPE
			SYNTAX Bit05251625
			MAX-ACCESS read-only
			STATUS current
			DESCRIPTION
				"Allows selecting the video output format"
		::= { gps3000p01v4Entry 7 }

		-- 1.3.6.1.4.1.10106.3.101291.1.1.9
		gps3000p01v4SdiVidHDelay OBJECT-TYPE
			SYNTAX DelayPixel1
			MAX-ACCESS read-write
			STATUS current
			DESCRIPTION
				"Allows adjusting the SDI video horizontal delay"
		::= { gps3000p01v4Entry 9 }

		-- 1.3.6.1.4.1.10106.3.101291.1.1.11
		gps3000p01v4SdiVidVDelay OBJECT-TYPE
			SYNTAX DelayLines1
			MAX-ACCESS read-write
			STATUS current
			DESCRIPTION
				"Allows adjusting the SDI video vertical delay"
		::= { gps3000p01v4Entry 11 }

		-- 1.3.6.1.4.1.10106.3.101291.1.1.13
		gps3000p01v4SdiVidFrDelay OBJECT-TYPE
			SYNTAX DelayFram1
			MAX-ACCESS read-write
			STATUS current
			DESCRIPTION
				"Allows adjusting the SDI video frame delay"
		::= { gps3000p01v4Entry 13 }

		-- 1.3.6.1.4.1.10106.3.101291.1.1.15
		gps3000p01v4AnaVidHDelay OBJECT-TYPE
			SYNTAX DelayPixel2
			MAX-ACCESS read-write
			STATUS current
			DESCRIPTION
				"Allows adjusting the Analog to SDI video horizontal delay"
		::= { gps3000p01v4Entry 15 }

		-- 1.3.6.1.4.1.10106.3.101291.1.1.17
		gps3000p01v4VitcInsLine OBJECT-TYPE
			SYNTAX VideoLine
			MAX-ACCESS read-write
			STATUS current
			DESCRIPTION
				"Allows adjusting the VITC insertion line"
		::= { gps3000p01v4Entry 17 }

		-- 1.3.6.1.4.1.10106.3.101291.1.1.19
		gps3000p01v4AnaVidSch OBJECT-TYPE
			SYNTAX Sch1
			MAX-ACCESS read-write
			STATUS current
			DESCRIPTION
				"Allows adjusting the Analog video SCH"
		::= { gps3000p01v4Entry 19 }

		-- 1.3.6.1.4.1.10106.3.101291.1.1.21
		gps3000p01v4HoldoverStat OBJECT-TYPE
			SYNTAX Bit0Trk1Hol
			MAX-ACCESS read-only
			STATUS current
			DESCRIPTION
				"Indicates if the module is locked to GPS or to reference or it is in holdover mode"
		::= { gps3000p01v4Entry 21 }

		-- 1.3.6.1.4.1.10106.3.101291.1.1.22
		gps3000p01v4HoldoverStatTrapEnable OBJECT-TYPE
			SYNTAX AlarmEnable
			MAX-ACCESS read-write
			STATUS current
			DESCRIPTION
				"Indicates if the module is locked to GPS or to reference or it is in holdover mode Trap Enable"
		::= { gps3000p01v4Entry 22 }

		-- 1.3.6.1.4.1.10106.3.101291.1.1.23
		gps3000p01v4RedundFail OBJECT-TYPE
			SYNTAX BitFail
			MAX-ACCESS read-only
			STATUS current
			DESCRIPTION
				"Indicates if there is any active module in the redundance system"
		::= { gps3000p01v4Entry 23 }

		-- 1.3.6.1.4.1.10106.3.101291.1.1.24
		gps3000p01v4RedundFailTrapEnable OBJECT-TYPE
			SYNTAX AlarmEnable
			MAX-ACCESS read-write
			STATUS current
			DESCRIPTION
				"Indicates if there is any active module in the redundance system Trap Enable"
		::= { gps3000p01v4Entry 24 }

		-- 1.3.6.1.4.1.10106.3.101291.1.1.25
		gps3000p01v4OutputsMuted OBJECT-TYPE
			SYNTAX BitFail
			MAX-ACCESS read-only
			STATUS current
			DESCRIPTION
				"Indicates f the module outputs are active"
		::= { gps3000p01v4Entry 25 }

		-- 1.3.6.1.4.1.10106.3.101291.1.1.26
		gps3000p01v4OutputsMutedTrapEnable OBJECT-TYPE
			SYNTAX AlarmEnable
			MAX-ACCESS read-write
			STATUS current
			DESCRIPTION
				"Indicates f the module outputs are active Trap Enable"
		::= { gps3000p01v4Entry 26 }

		-- 1.3.6.1.4.1.10106.3.101291.1.1.27
		gps3000p01v4SatRxStat OBJECT-TYPE
			SYNTAX GpsSatRxStat
			MAX-ACCESS read-only
			STATUS current
			DESCRIPTION
				"GPS receiver module satellite tracking status"
		::= { gps3000p01v4Entry 27 }

		-- 1.3.6.1.4.1.10106.3.101291.1.1.29
		gps3000p01v4AntenaStat OBJECT-TYPE
			SYNTAX GpsAntenaStat
			MAX-ACCESS read-only
			STATUS current
			DESCRIPTION
				"Antenna connection status"
		::= { gps3000p01v4Entry 29 }

		-- 1.3.6.1.4.1.10106.3.101291.1.1.30
		gps3000p01v4AntenaStatTrapEnable OBJECT-TYPE
			SYNTAX AlarmEnable
			MAX-ACCESS read-write
			STATUS current
			DESCRIPTION
				"Antenna connection status Trap Enable"
		::= { gps3000p01v4Entry 30 }

		-- 1.3.6.1.4.1.10106.3.101291.1.1.31
		gps3000p01v4SatNoFail OBJECT-TYPE
			SYNTAX BitFail
			MAX-ACCESS read-only
			STATUS current
			DESCRIPTION
				"Indicates that the number of visible satellites is low"
		::= { gps3000p01v4Entry 31 }

		-- 1.3.6.1.4.1.10106.3.101291.1.1.33
		gps3000p01v4AlmanacFail OBJECT-TYPE
			SYNTAX BitFail
			MAX-ACCESS read-only
			STATUS current
			DESCRIPTION
				"Indicates that the modules has an invalid almanac"
		::= { gps3000p01v4Entry 33 }

		-- 1.3.6.1.4.1.10106.3.101291.1.1.35
		gps3000p01v4GpsModFail OBJECT-TYPE
			SYNTAX BitFail
			MAX-ACCESS read-only
			STATUS current
			DESCRIPTION
				"Indicates that an error has been detected in the GPS receiver module"
		::= { gps3000p01v4Entry 35 }

		-- 1.3.6.1.4.1.10106.3.101291.1.1.37
		gps3000p01v4GpsTrackSats OBJECT-TYPE
			SYNTAX GpsSatellites
			MAX-ACCESS read-only
			STATUS current
			DESCRIPTION
				"Number of GPS tracking satellites"
		::= { gps3000p01v4Entry 37 }

		-- 1.3.6.1.4.1.10106.3.101291.1.1.39
		gps3000p01v4GpsVisibleSats OBJECT-TYPE
			SYNTAX GpsSatellites
			MAX-ACCESS read-only
			STATUS current
			DESCRIPTION
				"Number of GPS visible satellites"
		::= { gps3000p01v4Entry 39 }

		-- 1.3.6.1.4.1.10106.3.101291.1.1.41
		gps3000p01v4GpsSignalLevel OBJECT-TYPE
			SYNTAX LevelDbHz
			MAX-ACCESS read-only
			STATUS current
			DESCRIPTION
				"Estimated carrier to noise ratio for the best satellite in tracking"
		::= { gps3000p01v4Entry 41 }

		-- 1.3.6.1.4.1.10106.3.101291.1.1.43
		gps3000p01v4AdquisitionStat OBJECT-TYPE
			SYNTAX GpsAdqStat1
			MAX-ACCESS read-only
			STATUS current
			DESCRIPTION
				"GPS3000 module adquisition status"
		::= { gps3000p01v4Entry 43 }

		-- 1.3.6.1.4.1.10106.3.101291.1.1.45
		gps3000p01v4HoldoverTime OBJECT-TYPE
			SYNTAX GpsHoldovrTime
			MAX-ACCESS read-only
			STATUS current
			DESCRIPTION
				"Holdover time"
		::= { gps3000p01v4Entry 45 }

		-- 1.3.6.1.4.1.10106.3.101291.1.1.47
		gps3000p01v4FreqDriftEst OBJECT-TYPE
			SYNTAX GpsFrqDrftEst
			MAX-ACCESS read-only
			STATUS current
			DESCRIPTION
				"Frequency drift estimation"
		::= { gps3000p01v4Entry 47 }

		-- 1.3.6.1.4.1.10106.3.101291.1.1.49
		gps3000p01v4PhaseDriftEst OBJECT-TYPE
			SYNTAX GpsPhsDrftEst
			MAX-ACCESS read-only
			STATUS current
			DESCRIPTION
				"Phase drift estimation"
		::= { gps3000p01v4Entry 49 }

		-- 1.3.6.1.4.1.10106.3.207201
		sdt3000p01v1 OBJECT IDENTIFIER ::= { albalaProducts 207201 }

		-- 1.3.6.1.4.1.10106.3.207201.1
		sdt3000p01v1Table  OBJECT-TYPE
			SYNTAX SEQUENCE OF Sdt3000p01v1Entry
			MAX-ACCESS not-accessible
			STATUS current
			DESCRIPTION
				"Module  SDT3000P01V1 Table"
			::= { sdt3000p01v1 1 }

		-- 1.3.6.1.4.1.10106.3.207201.1.1
		sdt3000p01v1Entry  OBJECT-TYPE
			SYNTAX Sdt3000p01v1Entry
			MAX-ACCESS not-accessible
			STATUS current
			DESCRIPTION
				"Module SDT3000P01V1 Entry"
			INDEX { sdt3000p01v1Index }
			::= { sdt3000p01v1Table 1 }

			Sdt3000p01v1Entry ::=
			SEQUENCE {
				sdt3000p01v1Index
				ModuleIndex,
				sdt3000p01v1NoSigA
				BitFail,
				sdt3000p01v1NoSigATrapEnable
				AlarmEnable,
				sdt3000p01v1LaserFailA
				BitFail,
				sdt3000p01v1LaserFailATrapEnable
				AlarmEnable,
				sdt3000p01v1NoSigB
				BitFail,
				sdt3000p01v1NoSigBTrapEnable
				AlarmEnable,
				sdt3000p01v1LaserFailB
				BitFail,
				sdt3000p01v1LaserFailBTrapEnable
				AlarmEnable
			 }

		-- 1.3.6.1.4.1.10106.3.101291.1.1.1
		sdt3000p01v1Index OBJECT-TYPE
			SYNTAX ModuleIndex
			MAX-ACCESS read-only
			STATUS current
			DESCRIPTION
				"Index of SDT3000P01V1 Table"
		::= { sdt3000p01v1Entry 1 }

		-- 1.3.6.1.4.1.10106.3.101291.1.1.3
		sdt3000p01v1NoSigA OBJECT-TYPE
			SYNTAX BitFail
			MAX-ACCESS read-only
			STATUS current
			DESCRIPTION
				"Input signal status"
		::= { sdt3000p01v1Entry 3 }

		-- 1.3.6.1.4.1.10106.3.101291.1.1.4
		sdt3000p01v1NoSigATrapEnable OBJECT-TYPE
			SYNTAX AlarmEnable
			MAX-ACCESS read-write
			STATUS current
			DESCRIPTION
				"Input signal status Trap Enable"
		::= { sdt3000p01v1Entry 4 }

		-- 1.3.6.1.4.1.10106.3.101291.1.1.5
		sdt3000p01v1LaserFailA OBJECT-TYPE
			SYNTAX BitFail
			MAX-ACCESS read-only
			STATUS current
			DESCRIPTION
				"Laser status"
		::= { sdt3000p01v1Entry 5 }

		-- 1.3.6.1.4.1.10106.3.101291.1.1.6
		sdt3000p01v1LaserFailATrapEnable OBJECT-TYPE
			SYNTAX AlarmEnable
			MAX-ACCESS read-write
			STATUS current
			DESCRIPTION
				"Laser status Trap Enable"
		::= { sdt3000p01v1Entry 6 }

		-- 1.3.6.1.4.1.10106.3.101291.1.1.7
		sdt3000p01v1NoSigB OBJECT-TYPE
			SYNTAX BitFail
			MAX-ACCESS read-only
			STATUS current
			DESCRIPTION
				"Input signal status"
		::= { sdt3000p01v1Entry 7 }

		-- 1.3.6.1.4.1.10106.3.101291.1.1.8
		sdt3000p01v1NoSigBTrapEnable OBJECT-TYPE
			SYNTAX AlarmEnable
			MAX-ACCESS read-write
			STATUS current
			DESCRIPTION
				"Input signal status Trap Enable"
		::= { sdt3000p01v1Entry 8 }

		-- 1.3.6.1.4.1.10106.3.101291.1.1.9
		sdt3000p01v1LaserFailB OBJECT-TYPE
			SYNTAX BitFail
			MAX-ACCESS read-only
			STATUS current
			DESCRIPTION
				"Laser status"
		::= { sdt3000p01v1Entry 9 }

		-- 1.3.6.1.4.1.10106.3.101291.1.1.10
		sdt3000p01v1LaserFailBTrapEnable OBJECT-TYPE
			SYNTAX AlarmEnable
			MAX-ACCESS read-write
			STATUS current
			DESCRIPTION
				"Laser status Trap Enable"
		::= { sdt3000p01v1Entry 10 }

		-- 1.3.6.1.4.1.10106.3.207301
		sdr3000p01v1 OBJECT IDENTIFIER ::= { albalaProducts 207301 }

		-- 1.3.6.1.4.1.10106.3.207301.1
		sdr3000p01v1Table  OBJECT-TYPE
			SYNTAX SEQUENCE OF Sdr3000p01v1Entry
			MAX-ACCESS not-accessible
			STATUS current
			DESCRIPTION
				"Module  SDR3000P01V1 Table"
			::= { sdr3000p01v1 1 }

		-- 1.3.6.1.4.1.10106.3.207301.1.1
		sdr3000p01v1Entry  OBJECT-TYPE
			SYNTAX Sdr3000p01v1Entry
			MAX-ACCESS not-accessible
			STATUS current
			DESCRIPTION
				"Module SDR3000P01V1 Entry"
			INDEX { sdr3000p01v1Index }
			::= { sdr3000p01v1Table 1 }

			Sdr3000p01v1Entry ::=
			SEQUENCE {
				sdr3000p01v1Index
				ModuleIndex,
				sdr3000p01v1NoSigA
				BitFail,
				sdr3000p01v1NoSigATrapEnable
				AlarmEnable,
				sdr3000p01v1NoSigB
				BitFail,
				sdr3000p01v1NoSigBTrapEnable
				AlarmEnable,
				sdr3000p01v1RxPowerA
				Uint8,
				sdr3000p01v1RxPowerB
				Uint8
			 }

		-- 1.3.6.1.4.1.10106.3.101291.1.1.1
		sdr3000p01v1Index OBJECT-TYPE
			SYNTAX ModuleIndex
			MAX-ACCESS read-only
			STATUS current
			DESCRIPTION
				"Index of SDR3000P01V1 Table"
		::= { sdr3000p01v1Entry 1 }

		-- 1.3.6.1.4.1.10106.3.101291.1.1.3
		sdr3000p01v1NoSigA OBJECT-TYPE
			SYNTAX BitFail
			MAX-ACCESS read-only
			STATUS current
			DESCRIPTION
				"Input signal status"
		::= { sdr3000p01v1Entry 3 }

		-- 1.3.6.1.4.1.10106.3.101291.1.1.4
		sdr3000p01v1NoSigATrapEnable OBJECT-TYPE
			SYNTAX AlarmEnable
			MAX-ACCESS read-write
			STATUS current
			DESCRIPTION
				"Input signal status Trap Enable"
		::= { sdr3000p01v1Entry 4 }

		-- 1.3.6.1.4.1.10106.3.101291.1.1.5
		sdr3000p01v1NoSigB OBJECT-TYPE
			SYNTAX BitFail
			MAX-ACCESS read-only
			STATUS current
			DESCRIPTION
				"Input signal status"
		::= { sdr3000p01v1Entry 5 }

		-- 1.3.6.1.4.1.10106.3.101291.1.1.6
		sdr3000p01v1NoSigBTrapEnable OBJECT-TYPE
			SYNTAX AlarmEnable
			MAX-ACCESS read-write
			STATUS current
			DESCRIPTION
				"Input signal status Trap Enable"
		::= { sdr3000p01v1Entry 6 }

		-- 1.3.6.1.4.1.10106.3.101291.1.1.7
		sdr3000p01v1RxPowerA OBJECT-TYPE
			SYNTAX Uint8
			MAX-ACCESS read-only
			STATUS current
			DESCRIPTION
				"Inidcates the RX power"
		::= { sdr3000p01v1Entry 7 }

		-- 1.3.6.1.4.1.10106.3.101291.1.1.9
		sdr3000p01v1RxPowerB OBJECT-TYPE
			SYNTAX Uint8
			MAX-ACCESS read-only
			STATUS current
			DESCRIPTION
				"Inidcates the RX power"
		::= { sdr3000p01v1Entry 9 }

		-- 1.3.6.1.4.1.10106.3.211201
		dsw3000p05v1 OBJECT IDENTIFIER ::= { albalaProducts 211201 }

		-- 1.3.6.1.4.1.10106.3.211201.1
		dsw3000p05v1Table  OBJECT-TYPE
			SYNTAX SEQUENCE OF Dsw3000p05v1Entry
			MAX-ACCESS not-accessible
			STATUS current
			DESCRIPTION
				"Module  DSW3000P05V1 Table"
			::= { dsw3000p05v1 1 }

		-- 1.3.6.1.4.1.10106.3.211201.1.1
		dsw3000p05v1Entry  OBJECT-TYPE
			SYNTAX Dsw3000p05v1Entry
			MAX-ACCESS not-accessible
			STATUS current
			DESCRIPTION
				"Module DSW3000P05V1 Entry"
			INDEX { dsw3000p05v1Index }
			::= { dsw3000p05v1Table 1 }

			Dsw3000p05v1Entry ::=
			SEQUENCE {
				dsw3000p05v1Index
				ModuleIndex,
				dsw3000p05v1Mode
				ChgOverMode2,
				dsw3000p05v1ModeTrapEnable
				AlarmEnable,
				dsw3000p05v1Buzzer
				BitMask,
				dsw3000p05v1Input
				ChgOverInput1,
				dsw3000p05v1InputTrapEnable
				AlarmEnable,
				dsw3000p05v1MainFail
				BitFail,
				dsw3000p05v1MainFailTrapEnable
				AlarmEnable,
				dsw3000p05v1ExtMainFail
				BitFail,
				dsw3000p05v1ExtMainFailTrapEnable
				AlarmEnable,
				dsw3000p05v1ResFail
				BitFail,
				dsw3000p05v1ResFailTrapEnable
				AlarmEnable,
				dsw3000p05v1ExtResFail
				BitFail,
				dsw3000p05v1ExtResFailTrapEnable
				AlarmEnable,
				dsw3000p05v1AuxFail
				BitFail,
				dsw3000p05v1AuxFailTrapEnable
				AlarmEnable,
				dsw3000p05v1ExtAuxFail
				BitFail,
				dsw3000p05v1ExtAuxFailTrapEnable
				AlarmEnable
			 }

		-- 1.3.6.1.4.1.10106.3.101291.1.1.1
		dsw3000p05v1Index OBJECT-TYPE
			SYNTAX ModuleIndex
			MAX-ACCESS read-only
			STATUS current
			DESCRIPTION
				"Index of DSW3000P05V1 Table"
		::= { dsw3000p05v1Entry 1 }

		-- 1.3.6.1.4.1.10106.3.101291.1.1.3
		dsw3000p05v1Mode OBJECT-TYPE
			SYNTAX ChgOverMode2
			MAX-ACCESS read-write
			STATUS current
			DESCRIPTION
				"Allows selecting the switching mode"
		::= { dsw3000p05v1Entry 3 }

		-- 1.3.6.1.4.1.10106.3.101291.1.1.4
		dsw3000p05v1ModeTrapEnable OBJECT-TYPE
			SYNTAX AlarmEnable
			MAX-ACCESS read-write
			STATUS current
			DESCRIPTION
				"Allows selecting the switching mode Trap Enable"
		::= { dsw3000p05v1Entry 4 }

		-- 1.3.6.1.4.1.10106.3.101291.1.1.5
		dsw3000p05v1Buzzer OBJECT-TYPE
			SYNTAX BitMask
			MAX-ACCESS read-write
			STATUS current
			DESCRIPTION
				"Allows buzzer operation"
		::= { dsw3000p05v1Entry 5 }

		-- 1.3.6.1.4.1.10106.3.101291.1.1.7
		dsw3000p05v1Input OBJECT-TYPE
			SYNTAX ChgOverInput1
			MAX-ACCESS read-write
			STATUS current
			DESCRIPTION
				"Selected input"
		::= { dsw3000p05v1Entry 7 }

		-- 1.3.6.1.4.1.10106.3.101291.1.1.8
		dsw3000p05v1InputTrapEnable OBJECT-TYPE
			SYNTAX AlarmEnable
			MAX-ACCESS read-write
			STATUS current
			DESCRIPTION
				"Selected input Trap Enable"
		::= { dsw3000p05v1Entry 8 }

		-- 1.3.6.1.4.1.10106.3.101291.1.1.9
		dsw3000p05v1MainFail OBJECT-TYPE
			SYNTAX BitFail
			MAX-ACCESS read-only
			STATUS current
			DESCRIPTION
				"Main input status"
		::= { dsw3000p05v1Entry 9 }

		-- 1.3.6.1.4.1.10106.3.101291.1.1.10
		dsw3000p05v1MainFailTrapEnable OBJECT-TYPE
			SYNTAX AlarmEnable
			MAX-ACCESS read-write
			STATUS current
			DESCRIPTION
				"Main input status Trap Enable"
		::= { dsw3000p05v1Entry 10 }

		-- 1.3.6.1.4.1.10106.3.101291.1.1.11
		dsw3000p05v1ExtMainFail OBJECT-TYPE
			SYNTAX BitFail
			MAX-ACCESS read-only
			STATUS current
			DESCRIPTION
				"Main external input fail status"
		::= { dsw3000p05v1Entry 11 }

		-- 1.3.6.1.4.1.10106.3.101291.1.1.12
		dsw3000p05v1ExtMainFailTrapEnable OBJECT-TYPE
			SYNTAX AlarmEnable
			MAX-ACCESS read-write
			STATUS current
			DESCRIPTION
				"Main external input fail status Trap Enable"
		::= { dsw3000p05v1Entry 12 }

		-- 1.3.6.1.4.1.10106.3.101291.1.1.13
		dsw3000p05v1ResFail OBJECT-TYPE
			SYNTAX BitFail
			MAX-ACCESS read-only
			STATUS current
			DESCRIPTION
				"Reserve input status"
		::= { dsw3000p05v1Entry 13 }

		-- 1.3.6.1.4.1.10106.3.101291.1.1.14
		dsw3000p05v1ResFailTrapEnable OBJECT-TYPE
			SYNTAX AlarmEnable
			MAX-ACCESS read-write
			STATUS current
			DESCRIPTION
				"Reserve input status Trap Enable"
		::= { dsw3000p05v1Entry 14 }

		-- 1.3.6.1.4.1.10106.3.101291.1.1.15
		dsw3000p05v1ExtResFail OBJECT-TYPE
			SYNTAX BitFail
			MAX-ACCESS read-only
			STATUS current
			DESCRIPTION
				"Reserve external input fail status"
		::= { dsw3000p05v1Entry 15 }

		-- 1.3.6.1.4.1.10106.3.101291.1.1.16
		dsw3000p05v1ExtResFailTrapEnable OBJECT-TYPE
			SYNTAX AlarmEnable
			MAX-ACCESS read-write
			STATUS current
			DESCRIPTION
				"Reserve external input fail status Trap Enable"
		::= { dsw3000p05v1Entry 16 }

		-- 1.3.6.1.4.1.10106.3.101291.1.1.17
		dsw3000p05v1AuxFail OBJECT-TYPE
			SYNTAX BitFail
			MAX-ACCESS read-only
			STATUS current
			DESCRIPTION
				"Auxiliar input status"
		::= { dsw3000p05v1Entry 17 }

		-- 1.3.6.1.4.1.10106.3.101291.1.1.18
		dsw3000p05v1AuxFailTrapEnable OBJECT-TYPE
			SYNTAX AlarmEnable
			MAX-ACCESS read-write
			STATUS current
			DESCRIPTION
				"Auxiliar input status Trap Enable"
		::= { dsw3000p05v1Entry 18 }

		-- 1.3.6.1.4.1.10106.3.101291.1.1.19
		dsw3000p05v1ExtAuxFail OBJECT-TYPE
			SYNTAX BitFail
			MAX-ACCESS read-only
			STATUS current
			DESCRIPTION
				"Auxiliar external input fail status"
		::= { dsw3000p05v1Entry 19 }

		-- 1.3.6.1.4.1.10106.3.101291.1.1.20
		dsw3000p05v1ExtAuxFailTrapEnable OBJECT-TYPE
			SYNTAX AlarmEnable
			MAX-ACCESS read-write
			STATUS current
			DESCRIPTION
				"Auxiliar external input fail status Trap Enable"
		::= { dsw3000p05v1Entry 20 }

		-- 1.3.6.1.4.1.10106.3.213201
		gps3000p02v1 OBJECT IDENTIFIER ::= { albalaProducts 213201 }

		-- 1.3.6.1.4.1.10106.3.213201.1
		gps3000p02v1Table  OBJECT-TYPE
			SYNTAX SEQUENCE OF Gps3000p02v1Entry
			MAX-ACCESS not-accessible
			STATUS current
			DESCRIPTION
				"Module  GPS3000P02V1 Table"
			::= { gps3000p02v1 1 }

		-- 1.3.6.1.4.1.10106.3.213201.1.1
		gps3000p02v1Entry  OBJECT-TYPE
			SYNTAX Gps3000p02v1Entry
			MAX-ACCESS not-accessible
			STATUS current
			DESCRIPTION
				"Module GPS3000P02V1 Entry"
			INDEX { gps3000p02v1Index }
			::= { gps3000p02v1Table 1 }

			Gps3000p02v1Entry ::=
			SEQUENCE {
				gps3000p02v1Index
				ModuleIndex,
				gps3000p02v1Holdover
				Bit0Dis1Ena,
				gps3000p02v1HoldoverTrapEnable
				AlarmEnable,
				gps3000p02v1CableDelay
				DelayX2Ns,
				gps3000p02v1VideoOut
				Bit05251625,
				gps3000p02v1SdiVidHDelay
				DelayPixel1,
				gps3000p02v1SdiVidVDelay
				DelayLines1,
				gps3000p02v1SdiVidFrDelay
				DelayFram1,
				gps3000p02v1AnaVidHDelay
				DelayPixel2,
				gps3000p02v1VitcInsLine
				VideoLine,
				gps3000p02v1AnaVidSch
				Sch1,
				gps3000p02v1HoldoverStat
				Bit0Trk1Hol,
				gps3000p02v1HoldoverStatTrapEnable
				AlarmEnable,
				gps3000p02v1RedundFail
				BitFail,
				gps3000p02v1RedundFailTrapEnable
				AlarmEnable,
				gps3000p02v1OutputsMuted
				BitFail,
				gps3000p02v1OutputsMutedTrapEnable
				AlarmEnable,
				gps3000p02v1SatRxStat
				GpsSatRxStat,
				gps3000p02v1AntenaStat
				GpsAntenaStat,
				gps3000p02v1AntenaStatTrapEnable
				AlarmEnable,
				gps3000p02v1SatNoFail
				BitFail,
				gps3000p02v1AlmanacFail
				BitFail,
				gps3000p02v1GpsModFail
				BitFail,
				gps3000p02v1GpsTrackSats
				GpsSatellites,
				gps3000p02v1GpsVisibleSats
				GpsSatellites,
				gps3000p02v1GpsSignalLevel
				LevelDbHz,
				gps3000p02v1AdquisitionStat
				GpsAdqStat1,
				gps3000p02v1HoldoverTime
				GpsHoldovrTime,
				gps3000p02v1FreqDriftEst
				GpsFrqDrftEst,
				gps3000p02v1PhaseDriftEst
				GpsPhsDrftEst
			 }

		-- 1.3.6.1.4.1.10106.3.101291.1.1.1
		gps3000p02v1Index OBJECT-TYPE
			SYNTAX ModuleIndex
			MAX-ACCESS read-only
			STATUS current
			DESCRIPTION
				"Index of GPS3000P02V1 Table"
		::= { gps3000p02v1Entry 1 }

		-- 1.3.6.1.4.1.10106.3.101291.1.1.3
		gps3000p02v1Holdover OBJECT-TYPE
			SYNTAX Bit0Dis1Ena
			MAX-ACCESS read-write
			STATUS current
			DESCRIPTION
				"Allows setting the module in the holdover mode"
		::= { gps3000p02v1Entry 3 }

		-- 1.3.6.1.4.1.10106.3.101291.1.1.4
		gps3000p02v1HoldoverTrapEnable OBJECT-TYPE
			SYNTAX AlarmEnable
			MAX-ACCESS read-write
			STATUS current
			DESCRIPTION
				"Allows setting the module in the holdover mode Trap Enable"
		::= { gps3000p02v1Entry 4 }

		-- 1.3.6.1.4.1.10106.3.101291.1.1.5
		gps3000p02v1CableDelay OBJECT-TYPE
			SYNTAX DelayX2Ns
			MAX-ACCESS read-write
			STATUS current
			DESCRIPTION
				"Allows compensating the antenna cable delay"
		::= { gps3000p02v1Entry 5 }

		-- 1.3.6.1.4.1.10106.3.101291.1.1.7
		gps3000p02v1VideoOut OBJECT-TYPE
			SYNTAX Bit05251625
			MAX-ACCESS read-only
			STATUS current
			DESCRIPTION
				"Allows selecting the video output format"
		::= { gps3000p02v1Entry 7 }

		-- 1.3.6.1.4.1.10106.3.101291.1.1.9
		gps3000p02v1SdiVidHDelay OBJECT-TYPE
			SYNTAX DelayPixel1
			MAX-ACCESS read-write
			STATUS current
			DESCRIPTION
				"Allows adjusting the SDI video horizontal delay"
		::= { gps3000p02v1Entry 9 }

		-- 1.3.6.1.4.1.10106.3.101291.1.1.11
		gps3000p02v1SdiVidVDelay OBJECT-TYPE
			SYNTAX DelayLines1
			MAX-ACCESS read-write
			STATUS current
			DESCRIPTION
				"Allows adjusting the SDI video vertical delay"
		::= { gps3000p02v1Entry 11 }

		-- 1.3.6.1.4.1.10106.3.101291.1.1.13
		gps3000p02v1SdiVidFrDelay OBJECT-TYPE
			SYNTAX DelayFram1
			MAX-ACCESS read-write
			STATUS current
			DESCRIPTION
				"Allows adjusting the SDI video frame delay"
		::= { gps3000p02v1Entry 13 }

		-- 1.3.6.1.4.1.10106.3.101291.1.1.15
		gps3000p02v1AnaVidHDelay OBJECT-TYPE
			SYNTAX DelayPixel2
			MAX-ACCESS read-write
			STATUS current
			DESCRIPTION
				"Allows adjusting the Analog to SDI video horizontal delay"
		::= { gps3000p02v1Entry 15 }

		-- 1.3.6.1.4.1.10106.3.101291.1.1.17
		gps3000p02v1VitcInsLine OBJECT-TYPE
			SYNTAX VideoLine
			MAX-ACCESS read-write
			STATUS current
			DESCRIPTION
				"Allows adjusting the VITC insertion line"
		::= { gps3000p02v1Entry 17 }

		-- 1.3.6.1.4.1.10106.3.101291.1.1.19
		gps3000p02v1AnaVidSch OBJECT-TYPE
			SYNTAX Sch1
			MAX-ACCESS read-write
			STATUS current
			DESCRIPTION
				"Allows adjusting the Analog video SCH"
		::= { gps3000p02v1Entry 19 }

		-- 1.3.6.1.4.1.10106.3.101291.1.1.21
		gps3000p02v1HoldoverStat OBJECT-TYPE
			SYNTAX Bit0Trk1Hol
			MAX-ACCESS read-only
			STATUS current
			DESCRIPTION
				"Indicates if the module is locked to GPS or to reference or it is in holdover mode"
		::= { gps3000p02v1Entry 21 }

		-- 1.3.6.1.4.1.10106.3.101291.1.1.22
		gps3000p02v1HoldoverStatTrapEnable OBJECT-TYPE
			SYNTAX AlarmEnable
			MAX-ACCESS read-write
			STATUS current
			DESCRIPTION
				"Indicates if the module is locked to GPS or to reference or it is in holdover mode Trap Enable"
		::= { gps3000p02v1Entry 22 }

		-- 1.3.6.1.4.1.10106.3.101291.1.1.23
		gps3000p02v1RedundFail OBJECT-TYPE
			SYNTAX BitFail
			MAX-ACCESS read-only
			STATUS current
			DESCRIPTION
				"Indicates if there is any active module in the redundance system"
		::= { gps3000p02v1Entry 23 }

		-- 1.3.6.1.4.1.10106.3.101291.1.1.24
		gps3000p02v1RedundFailTrapEnable OBJECT-TYPE
			SYNTAX AlarmEnable
			MAX-ACCESS read-write
			STATUS current
			DESCRIPTION
				"Indicates if there is any active module in the redundance system Trap Enable"
		::= { gps3000p02v1Entry 24 }

		-- 1.3.6.1.4.1.10106.3.101291.1.1.25
		gps3000p02v1OutputsMuted OBJECT-TYPE
			SYNTAX BitFail
			MAX-ACCESS read-only
			STATUS current
			DESCRIPTION
				"Indicates f the module outputs are active"
		::= { gps3000p02v1Entry 25 }

		-- 1.3.6.1.4.1.10106.3.101291.1.1.26
		gps3000p02v1OutputsMutedTrapEnable OBJECT-TYPE
			SYNTAX AlarmEnable
			MAX-ACCESS read-write
			STATUS current
			DESCRIPTION
				"Indicates f the module outputs are active Trap Enable"
		::= { gps3000p02v1Entry 26 }

		-- 1.3.6.1.4.1.10106.3.101291.1.1.27
		gps3000p02v1SatRxStat OBJECT-TYPE
			SYNTAX GpsSatRxStat
			MAX-ACCESS read-only
			STATUS current
			DESCRIPTION
				"GPS receiver module satellite tracking status"
		::= { gps3000p02v1Entry 27 }

		-- 1.3.6.1.4.1.10106.3.101291.1.1.29
		gps3000p02v1AntenaStat OBJECT-TYPE
			SYNTAX GpsAntenaStat
			MAX-ACCESS read-only
			STATUS current
			DESCRIPTION
				"Antenna connection status"
		::= { gps3000p02v1Entry 29 }

		-- 1.3.6.1.4.1.10106.3.101291.1.1.30
		gps3000p02v1AntenaStatTrapEnable OBJECT-TYPE
			SYNTAX AlarmEnable
			MAX-ACCESS read-write
			STATUS current
			DESCRIPTION
				"Antenna connection status Trap Enable"
		::= { gps3000p02v1Entry 30 }

		-- 1.3.6.1.4.1.10106.3.101291.1.1.31
		gps3000p02v1SatNoFail OBJECT-TYPE
			SYNTAX BitFail
			MAX-ACCESS read-only
			STATUS current
			DESCRIPTION
				"Indicates that the number of visible satellites is low"
		::= { gps3000p02v1Entry 31 }

		-- 1.3.6.1.4.1.10106.3.101291.1.1.33
		gps3000p02v1AlmanacFail OBJECT-TYPE
			SYNTAX BitFail
			MAX-ACCESS read-only
			STATUS current
			DESCRIPTION
				"Indicates that the modules has an invalid almanac"
		::= { gps3000p02v1Entry 33 }

		-- 1.3.6.1.4.1.10106.3.101291.1.1.35
		gps3000p02v1GpsModFail OBJECT-TYPE
			SYNTAX BitFail
			MAX-ACCESS read-only
			STATUS current
			DESCRIPTION
				"Indicates that an error has been detected in the GPS receiver module"
		::= { gps3000p02v1Entry 35 }

		-- 1.3.6.1.4.1.10106.3.101291.1.1.37
		gps3000p02v1GpsTrackSats OBJECT-TYPE
			SYNTAX GpsSatellites
			MAX-ACCESS read-only
			STATUS current
			DESCRIPTION
				"Number of GPS tracking satellites"
		::= { gps3000p02v1Entry 37 }

		-- 1.3.6.1.4.1.10106.3.101291.1.1.39
		gps3000p02v1GpsVisibleSats OBJECT-TYPE
			SYNTAX GpsSatellites
			MAX-ACCESS read-only
			STATUS current
			DESCRIPTION
				"Number of GPS visible satellites"
		::= { gps3000p02v1Entry 39 }

		-- 1.3.6.1.4.1.10106.3.101291.1.1.41
		gps3000p02v1GpsSignalLevel OBJECT-TYPE
			SYNTAX LevelDbHz
			MAX-ACCESS read-only
			STATUS current
			DESCRIPTION
				"Estimated carrier to noise ratio for the best satellite in tracking"
		::= { gps3000p02v1Entry 41 }

		-- 1.3.6.1.4.1.10106.3.101291.1.1.43
		gps3000p02v1AdquisitionStat OBJECT-TYPE
			SYNTAX GpsAdqStat1
			MAX-ACCESS read-only
			STATUS current
			DESCRIPTION
				"GPS3000 module adquisition status"
		::= { gps3000p02v1Entry 43 }

		-- 1.3.6.1.4.1.10106.3.101291.1.1.45
		gps3000p02v1HoldoverTime OBJECT-TYPE
			SYNTAX GpsHoldovrTime
			MAX-ACCESS read-only
			STATUS current
			DESCRIPTION
				"Holdover time"
		::= { gps3000p02v1Entry 45 }

		-- 1.3.6.1.4.1.10106.3.101291.1.1.47
		gps3000p02v1FreqDriftEst OBJECT-TYPE
			SYNTAX GpsFrqDrftEst
			MAX-ACCESS read-only
			STATUS current
			DESCRIPTION
				"Frequency drift estimation"
		::= { gps3000p02v1Entry 47 }

		-- 1.3.6.1.4.1.10106.3.101291.1.1.49
		gps3000p02v1PhaseDriftEst OBJECT-TYPE
			SYNTAX GpsPhsDrftEst
			MAX-ACCESS read-only
			STATUS current
			DESCRIPTION
				"Phase drift estimation"
		::= { gps3000p02v1Entry 49 }

		-- 1.3.6.1.4.1.10106.3.213202
		gps3000p02v2 OBJECT IDENTIFIER ::= { albalaProducts 213202 }

		-- 1.3.6.1.4.1.10106.3.213202.1
		gps3000p02v2Table  OBJECT-TYPE
			SYNTAX SEQUENCE OF Gps3000p02v2Entry
			MAX-ACCESS not-accessible
			STATUS current
			DESCRIPTION
				"Module  GPS3000P02V2 Table"
			::= { gps3000p02v2 1 }

		-- 1.3.6.1.4.1.10106.3.213202.1.1
		gps3000p02v2Entry  OBJECT-TYPE
			SYNTAX Gps3000p02v2Entry
			MAX-ACCESS not-accessible
			STATUS current
			DESCRIPTION
				"Module GPS3000P02V2 Entry"
			INDEX { gps3000p02v2Index }
			::= { gps3000p02v2Table 1 }

			Gps3000p02v2Entry ::=
			SEQUENCE {
				gps3000p02v2Index
				ModuleIndex,
				gps3000p02v2Holdover
				Bit0Dis1Ena,
				gps3000p02v2HoldoverTrapEnable
				AlarmEnable,
				gps3000p02v2CableDelay
				DelayX2Ns,
				gps3000p02v2VideoOut
				Bit05251625,
				gps3000p02v2SdiVidHDelay
				DelayPixel1,
				gps3000p02v2SdiVidVDelay
				DelayLines1,
				gps3000p02v2SdiVidFrDelay
				DelayFram1,
				gps3000p02v2AnaVidHDelay
				DelayPixel2,
				gps3000p02v2VitcInsLine
				VideoLine,
				gps3000p02v2AnaVidSch
				Sch1,
				gps3000p02v2HoldoverStat
				Bit0Trk1Hol,
				gps3000p02v2HoldoverStatTrapEnable
				AlarmEnable,
				gps3000p02v2RedundFail
				BitFail,
				gps3000p02v2RedundFailTrapEnable
				AlarmEnable,
				gps3000p02v2OutputsMuted
				BitFail,
				gps3000p02v2OutputsMutedTrapEnable
				AlarmEnable,
				gps3000p02v2SatRxStat
				GpsSatRxStat,
				gps3000p02v2AntenaStat
				GpsAntenaStat,
				gps3000p02v2AntenaStatTrapEnable
				AlarmEnable,
				gps3000p02v2SatNoFail
				BitFail,
				gps3000p02v2AlmanacFail
				BitFail,
				gps3000p02v2GpsModFail
				BitFail,
				gps3000p02v2GpsTrackSats
				GpsSatellites,
				gps3000p02v2GpsVisibleSats
				GpsSatellites,
				gps3000p02v2GpsSignalLevel
				LevelDbHz,
				gps3000p02v2AdquisitionStat
				GpsAdqStat1,
				gps3000p02v2HoldoverTime
				GpsHoldovrTime,
				gps3000p02v2FreqDriftEst
				GpsFrqDrftEst,
				gps3000p02v2PhaseDriftEst
				GpsPhsDrftEst
			 }

		-- 1.3.6.1.4.1.10106.3.101291.1.1.1
		gps3000p02v2Index OBJECT-TYPE
			SYNTAX ModuleIndex
			MAX-ACCESS read-only
			STATUS current
			DESCRIPTION
				"Index of GPS3000P02V2 Table"
		::= { gps3000p02v2Entry 1 }

		-- 1.3.6.1.4.1.10106.3.101291.1.1.3
		gps3000p02v2Holdover OBJECT-TYPE
			SYNTAX Bit0Dis1Ena
			MAX-ACCESS read-write
			STATUS current
			DESCRIPTION
				"Allows setting the module in the holdover mode"
		::= { gps3000p02v2Entry 3 }

		-- 1.3.6.1.4.1.10106.3.101291.1.1.4
		gps3000p02v2HoldoverTrapEnable OBJECT-TYPE
			SYNTAX AlarmEnable
			MAX-ACCESS read-write
			STATUS current
			DESCRIPTION
				"Allows setting the module in the holdover mode Trap Enable"
		::= { gps3000p02v2Entry 4 }

		-- 1.3.6.1.4.1.10106.3.101291.1.1.5
		gps3000p02v2CableDelay OBJECT-TYPE
			SYNTAX DelayX2Ns
			MAX-ACCESS read-write
			STATUS current
			DESCRIPTION
				"Allows compensating the antenna cable delay"
		::= { gps3000p02v2Entry 5 }

		-- 1.3.6.1.4.1.10106.3.101291.1.1.7
		gps3000p02v2VideoOut OBJECT-TYPE
			SYNTAX Bit05251625
			MAX-ACCESS read-only
			STATUS current
			DESCRIPTION
				"Allows selecting the video output format"
		::= { gps3000p02v2Entry 7 }

		-- 1.3.6.1.4.1.10106.3.101291.1.1.9
		gps3000p02v2SdiVidHDelay OBJECT-TYPE
			SYNTAX DelayPixel1
			MAX-ACCESS read-write
			STATUS current
			DESCRIPTION
				"Allows adjusting the SDI video horizontal delay"
		::= { gps3000p02v2Entry 9 }

		-- 1.3.6.1.4.1.10106.3.101291.1.1.11
		gps3000p02v2SdiVidVDelay OBJECT-TYPE
			SYNTAX DelayLines1
			MAX-ACCESS read-write
			STATUS current
			DESCRIPTION
				"Allows adjusting the SDI video vertical delay"
		::= { gps3000p02v2Entry 11 }

		-- 1.3.6.1.4.1.10106.3.101291.1.1.13
		gps3000p02v2SdiVidFrDelay OBJECT-TYPE
			SYNTAX DelayFram1
			MAX-ACCESS read-write
			STATUS current
			DESCRIPTION
				"Allows adjusting the SDI video frame delay"
		::= { gps3000p02v2Entry 13 }

		-- 1.3.6.1.4.1.10106.3.101291.1.1.15
		gps3000p02v2AnaVidHDelay OBJECT-TYPE
			SYNTAX DelayPixel2
			MAX-ACCESS read-write
			STATUS current
			DESCRIPTION
				"Allows adjusting the Analog to SDI video horizontal delay"
		::= { gps3000p02v2Entry 15 }

		-- 1.3.6.1.4.1.10106.3.101291.1.1.17
		gps3000p02v2VitcInsLine OBJECT-TYPE
			SYNTAX VideoLine
			MAX-ACCESS read-write
			STATUS current
			DESCRIPTION
				"Allows adjusting the VITC insertion line"
		::= { gps3000p02v2Entry 17 }

		-- 1.3.6.1.4.1.10106.3.101291.1.1.19
		gps3000p02v2AnaVidSch OBJECT-TYPE
			SYNTAX Sch1
			MAX-ACCESS read-write
			STATUS current
			DESCRIPTION
				"Allows adjusting the Analog video SCH"
		::= { gps3000p02v2Entry 19 }

		-- 1.3.6.1.4.1.10106.3.101291.1.1.21
		gps3000p02v2HoldoverStat OBJECT-TYPE
			SYNTAX Bit0Trk1Hol
			MAX-ACCESS read-only
			STATUS current
			DESCRIPTION
				"Indicates if the module is locked to GPS or to reference or it is in holdover mode"
		::= { gps3000p02v2Entry 21 }

		-- 1.3.6.1.4.1.10106.3.101291.1.1.22
		gps3000p02v2HoldoverStatTrapEnable OBJECT-TYPE
			SYNTAX AlarmEnable
			MAX-ACCESS read-write
			STATUS current
			DESCRIPTION
				"Indicates if the module is locked to GPS or to reference or it is in holdover mode Trap Enable"
		::= { gps3000p02v2Entry 22 }

		-- 1.3.6.1.4.1.10106.3.101291.1.1.23
		gps3000p02v2RedundFail OBJECT-TYPE
			SYNTAX BitFail
			MAX-ACCESS read-only
			STATUS current
			DESCRIPTION
				"Indicates if there is any active module in the redundance system"
		::= { gps3000p02v2Entry 23 }

		-- 1.3.6.1.4.1.10106.3.101291.1.1.24
		gps3000p02v2RedundFailTrapEnable OBJECT-TYPE
			SYNTAX AlarmEnable
			MAX-ACCESS read-write
			STATUS current
			DESCRIPTION
				"Indicates if there is any active module in the redundance system Trap Enable"
		::= { gps3000p02v2Entry 24 }

		-- 1.3.6.1.4.1.10106.3.101291.1.1.25
		gps3000p02v2OutputsMuted OBJECT-TYPE
			SYNTAX BitFail
			MAX-ACCESS read-only
			STATUS current
			DESCRIPTION
				"Indicates f the module outputs are active"
		::= { gps3000p02v2Entry 25 }

		-- 1.3.6.1.4.1.10106.3.101291.1.1.26
		gps3000p02v2OutputsMutedTrapEnable OBJECT-TYPE
			SYNTAX AlarmEnable
			MAX-ACCESS read-write
			STATUS current
			DESCRIPTION
				"Indicates f the module outputs are active Trap Enable"
		::= { gps3000p02v2Entry 26 }

		-- 1.3.6.1.4.1.10106.3.101291.1.1.27
		gps3000p02v2SatRxStat OBJECT-TYPE
			SYNTAX GpsSatRxStat
			MAX-ACCESS read-only
			STATUS current
			DESCRIPTION
				"GPS receiver module satellite tracking status"
		::= { gps3000p02v2Entry 27 }

		-- 1.3.6.1.4.1.10106.3.101291.1.1.29
		gps3000p02v2AntenaStat OBJECT-TYPE
			SYNTAX GpsAntenaStat
			MAX-ACCESS read-only
			STATUS current
			DESCRIPTION
				"Antenna connection status"
		::= { gps3000p02v2Entry 29 }

		-- 1.3.6.1.4.1.10106.3.101291.1.1.30
		gps3000p02v2AntenaStatTrapEnable OBJECT-TYPE
			SYNTAX AlarmEnable
			MAX-ACCESS read-write
			STATUS current
			DESCRIPTION
				"Antenna connection status Trap Enable"
		::= { gps3000p02v2Entry 30 }

		-- 1.3.6.1.4.1.10106.3.101291.1.1.31
		gps3000p02v2SatNoFail OBJECT-TYPE
			SYNTAX BitFail
			MAX-ACCESS read-only
			STATUS current
			DESCRIPTION
				"Indicates that the number of visible satellites is low"
		::= { gps3000p02v2Entry 31 }

		-- 1.3.6.1.4.1.10106.3.101291.1.1.33
		gps3000p02v2AlmanacFail OBJECT-TYPE
			SYNTAX BitFail
			MAX-ACCESS read-only
			STATUS current
			DESCRIPTION
				"Indicates that the modules has an invalid almanac"
		::= { gps3000p02v2Entry 33 }

		-- 1.3.6.1.4.1.10106.3.101291.1.1.35
		gps3000p02v2GpsModFail OBJECT-TYPE
			SYNTAX BitFail
			MAX-ACCESS read-only
			STATUS current
			DESCRIPTION
				"Indicates that an error has been detected in the GPS receiver module"
		::= { gps3000p02v2Entry 35 }

		-- 1.3.6.1.4.1.10106.3.101291.1.1.37
		gps3000p02v2GpsTrackSats OBJECT-TYPE
			SYNTAX GpsSatellites
			MAX-ACCESS read-only
			STATUS current
			DESCRIPTION
				"Number of GPS tracking satellites"
		::= { gps3000p02v2Entry 37 }

		-- 1.3.6.1.4.1.10106.3.101291.1.1.39
		gps3000p02v2GpsVisibleSats OBJECT-TYPE
			SYNTAX GpsSatellites
			MAX-ACCESS read-only
			STATUS current
			DESCRIPTION
				"Number of GPS visible satellites"
		::= { gps3000p02v2Entry 39 }

		-- 1.3.6.1.4.1.10106.3.101291.1.1.41
		gps3000p02v2GpsSignalLevel OBJECT-TYPE
			SYNTAX LevelDbHz
			MAX-ACCESS read-only
			STATUS current
			DESCRIPTION
				"Estimated carrier to noise ratio for the best satellite in tracking"
		::= { gps3000p02v2Entry 41 }

		-- 1.3.6.1.4.1.10106.3.101291.1.1.43
		gps3000p02v2AdquisitionStat OBJECT-TYPE
			SYNTAX GpsAdqStat1
			MAX-ACCESS read-only
			STATUS current
			DESCRIPTION
				"GPS3000 module adquisition status"
		::= { gps3000p02v2Entry 43 }

		-- 1.3.6.1.4.1.10106.3.101291.1.1.45
		gps3000p02v2HoldoverTime OBJECT-TYPE
			SYNTAX GpsHoldovrTime
			MAX-ACCESS read-only
			STATUS current
			DESCRIPTION
				"Holdover time"
		::= { gps3000p02v2Entry 45 }

		-- 1.3.6.1.4.1.10106.3.101291.1.1.47
		gps3000p02v2FreqDriftEst OBJECT-TYPE
			SYNTAX GpsFrqDrftEst
			MAX-ACCESS read-only
			STATUS current
			DESCRIPTION
				"Frequency drift estimation"
		::= { gps3000p02v2Entry 47 }

		-- 1.3.6.1.4.1.10106.3.101291.1.1.49
		gps3000p02v2PhaseDriftEst OBJECT-TYPE
			SYNTAX GpsPhsDrftEst
			MAX-ACCESS read-only
			STATUS current
			DESCRIPTION
				"Phase drift estimation"
		::= { gps3000p02v2Entry 49 }

		-- 1.3.6.1.4.1.10106.3.213203
		gps3000p02v3 OBJECT IDENTIFIER ::= { albalaProducts 213203 }

		-- 1.3.6.1.4.1.10106.3.213203.1
		gps3000p02v3Table  OBJECT-TYPE
			SYNTAX SEQUENCE OF Gps3000p02v3Entry
			MAX-ACCESS not-accessible
			STATUS current
			DESCRIPTION
				"Module  GPS3000P02V3 Table"
			::= { gps3000p02v3 1 }

		-- 1.3.6.1.4.1.10106.3.213203.1.1
		gps3000p02v3Entry  OBJECT-TYPE
			SYNTAX Gps3000p02v3Entry
			MAX-ACCESS not-accessible
			STATUS current
			DESCRIPTION
				"Module GPS3000P02V3 Entry"
			INDEX { gps3000p02v3Index }
			::= { gps3000p02v3Table 1 }

			Gps3000p02v3Entry ::=
			SEQUENCE {
				gps3000p02v3Index
				ModuleIndex,
				gps3000p02v3Holdover
				Bit0Dis1Ena,
				gps3000p02v3HoldoverTrapEnable
				AlarmEnable,
				gps3000p02v3CableDelay
				DelayX2Ns,
				gps3000p02v3VideoOut
				Bit05251625,
				gps3000p02v3SdiVidHDelay
				DelayPixel1,
				gps3000p02v3SdiVidVDelay
				DelayLines1,
				gps3000p02v3SdiVidFrDelay
				DelayFram1,
				gps3000p02v3AnaVidHDelay
				DelayPixel2,
				gps3000p02v3VitcInsLine
				VideoLine,
				gps3000p02v3AnaVidSch
				Sch1,
				gps3000p02v3HoldoverStat
				Bit0Trk1Hol,
				gps3000p02v3HoldoverStatTrapEnable
				AlarmEnable,
				gps3000p02v3RedundFail
				BitFail,
				gps3000p02v3RedundFailTrapEnable
				AlarmEnable,
				gps3000p02v3OutputsMuted
				BitFail,
				gps3000p02v3OutputsMutedTrapEnable
				AlarmEnable,
				gps3000p02v3SatRxStat
				GpsSatRxStat,
				gps3000p02v3AntenaStat
				GpsAntenaStat,
				gps3000p02v3AntenaStatTrapEnable
				AlarmEnable,
				gps3000p02v3SatNoFail
				BitFail,
				gps3000p02v3AlmanacFail
				BitFail,
				gps3000p02v3GpsModFail
				BitFail,
				gps3000p02v3GpsTrackSats
				GpsSatellites,
				gps3000p02v3GpsVisibleSats
				GpsSatellites,
				gps3000p02v3GpsSignalLevel
				LevelDbHz,
				gps3000p02v3AdquisitionStat
				GpsAdqStat1,
				gps3000p02v3HoldoverTime
				GpsHoldovrTime,
				gps3000p02v3FreqDriftEst
				GpsFrqDrftEst,
				gps3000p02v3PhaseDriftEst
				GpsPhsDrftEst
			 }

		-- 1.3.6.1.4.1.10106.3.101291.1.1.1
		gps3000p02v3Index OBJECT-TYPE
			SYNTAX ModuleIndex
			MAX-ACCESS read-only
			STATUS current
			DESCRIPTION
				"Index of GPS3000P02V3 Table"
		::= { gps3000p02v3Entry 1 }

		-- 1.3.6.1.4.1.10106.3.101291.1.1.3
		gps3000p02v3Holdover OBJECT-TYPE
			SYNTAX Bit0Dis1Ena
			MAX-ACCESS read-write
			STATUS current
			DESCRIPTION
				"Allows setting the module in the holdover mode"
		::= { gps3000p02v3Entry 3 }

		-- 1.3.6.1.4.1.10106.3.101291.1.1.4
		gps3000p02v3HoldoverTrapEnable OBJECT-TYPE
			SYNTAX AlarmEnable
			MAX-ACCESS read-write
			STATUS current
			DESCRIPTION
				"Allows setting the module in the holdover mode Trap Enable"
		::= { gps3000p02v3Entry 4 }

		-- 1.3.6.1.4.1.10106.3.101291.1.1.5
		gps3000p02v3CableDelay OBJECT-TYPE
			SYNTAX DelayX2Ns
			MAX-ACCESS read-write
			STATUS current
			DESCRIPTION
				"Allows compensating the antenna cable delay"
		::= { gps3000p02v3Entry 5 }

		-- 1.3.6.1.4.1.10106.3.101291.1.1.7
		gps3000p02v3VideoOut OBJECT-TYPE
			SYNTAX Bit05251625
			MAX-ACCESS read-only
			STATUS current
			DESCRIPTION
				"Allows selecting the video output format"
		::= { gps3000p02v3Entry 7 }

		-- 1.3.6.1.4.1.10106.3.101291.1.1.9
		gps3000p02v3SdiVidHDelay OBJECT-TYPE
			SYNTAX DelayPixel1
			MAX-ACCESS read-write
			STATUS current
			DESCRIPTION
				"Allows adjusting the SDI video horizontal delay"
		::= { gps3000p02v3Entry 9 }

		-- 1.3.6.1.4.1.10106.3.101291.1.1.11
		gps3000p02v3SdiVidVDelay OBJECT-TYPE
			SYNTAX DelayLines1
			MAX-ACCESS read-write
			STATUS current
			DESCRIPTION
				"Allows adjusting the SDI video vertical delay"
		::= { gps3000p02v3Entry 11 }

		-- 1.3.6.1.4.1.10106.3.101291.1.1.13
		gps3000p02v3SdiVidFrDelay OBJECT-TYPE
			SYNTAX DelayFram1
			MAX-ACCESS read-write
			STATUS current
			DESCRIPTION
				"Allows adjusting the SDI video frame delay"
		::= { gps3000p02v3Entry 13 }

		-- 1.3.6.1.4.1.10106.3.101291.1.1.15
		gps3000p02v3AnaVidHDelay OBJECT-TYPE
			SYNTAX DelayPixel2
			MAX-ACCESS read-write
			STATUS current
			DESCRIPTION
				"Allows adjusting the Analog to SDI video horizontal delay"
		::= { gps3000p02v3Entry 15 }

		-- 1.3.6.1.4.1.10106.3.101291.1.1.17
		gps3000p02v3VitcInsLine OBJECT-TYPE
			SYNTAX VideoLine
			MAX-ACCESS read-write
			STATUS current
			DESCRIPTION
				"Allows adjusting the VITC insertion line"
		::= { gps3000p02v3Entry 17 }

		-- 1.3.6.1.4.1.10106.3.101291.1.1.19
		gps3000p02v3AnaVidSch OBJECT-TYPE
			SYNTAX Sch1
			MAX-ACCESS read-write
			STATUS current
			DESCRIPTION
				"Allows adjusting the Analog video SCH"
		::= { gps3000p02v3Entry 19 }

		-- 1.3.6.1.4.1.10106.3.101291.1.1.21
		gps3000p02v3HoldoverStat OBJECT-TYPE
			SYNTAX Bit0Trk1Hol
			MAX-ACCESS read-only
			STATUS current
			DESCRIPTION
				"Indicates if the module is locked to GPS or to reference or it is in holdover mode"
		::= { gps3000p02v3Entry 21 }

		-- 1.3.6.1.4.1.10106.3.101291.1.1.22
		gps3000p02v3HoldoverStatTrapEnable OBJECT-TYPE
			SYNTAX AlarmEnable
			MAX-ACCESS read-write
			STATUS current
			DESCRIPTION
				"Indicates if the module is locked to GPS or to reference or it is in holdover mode Trap Enable"
		::= { gps3000p02v3Entry 22 }

		-- 1.3.6.1.4.1.10106.3.101291.1.1.23
		gps3000p02v3RedundFail OBJECT-TYPE
			SYNTAX BitFail
			MAX-ACCESS read-only
			STATUS current
			DESCRIPTION
				"Indicates if there is any active module in the redundance system"
		::= { gps3000p02v3Entry 23 }

		-- 1.3.6.1.4.1.10106.3.101291.1.1.24
		gps3000p02v3RedundFailTrapEnable OBJECT-TYPE
			SYNTAX AlarmEnable
			MAX-ACCESS read-write
			STATUS current
			DESCRIPTION
				"Indicates if there is any active module in the redundance system Trap Enable"
		::= { gps3000p02v3Entry 24 }

		-- 1.3.6.1.4.1.10106.3.101291.1.1.25
		gps3000p02v3OutputsMuted OBJECT-TYPE
			SYNTAX BitFail
			MAX-ACCESS read-only
			STATUS current
			DESCRIPTION
				"Indicates f the module outputs are active"
		::= { gps3000p02v3Entry 25 }

		-- 1.3.6.1.4.1.10106.3.101291.1.1.26
		gps3000p02v3OutputsMutedTrapEnable OBJECT-TYPE
			SYNTAX AlarmEnable
			MAX-ACCESS read-write
			STATUS current
			DESCRIPTION
				"Indicates f the module outputs are active Trap Enable"
		::= { gps3000p02v3Entry 26 }

		-- 1.3.6.1.4.1.10106.3.101291.1.1.27
		gps3000p02v3SatRxStat OBJECT-TYPE
			SYNTAX GpsSatRxStat
			MAX-ACCESS read-only
			STATUS current
			DESCRIPTION
				"GPS receiver module satellite tracking status"
		::= { gps3000p02v3Entry 27 }

		-- 1.3.6.1.4.1.10106.3.101291.1.1.29
		gps3000p02v3AntenaStat OBJECT-TYPE
			SYNTAX GpsAntenaStat
			MAX-ACCESS read-only
			STATUS current
			DESCRIPTION
				"Antenna connection status"
		::= { gps3000p02v3Entry 29 }

		-- 1.3.6.1.4.1.10106.3.101291.1.1.30
		gps3000p02v3AntenaStatTrapEnable OBJECT-TYPE
			SYNTAX AlarmEnable
			MAX-ACCESS read-write
			STATUS current
			DESCRIPTION
				"Antenna connection status Trap Enable"
		::= { gps3000p02v3Entry 30 }

		-- 1.3.6.1.4.1.10106.3.101291.1.1.31
		gps3000p02v3SatNoFail OBJECT-TYPE
			SYNTAX BitFail
			MAX-ACCESS read-only
			STATUS current
			DESCRIPTION
				"Indicates that the number of visible satellites is low"
		::= { gps3000p02v3Entry 31 }

		-- 1.3.6.1.4.1.10106.3.101291.1.1.33
		gps3000p02v3AlmanacFail OBJECT-TYPE
			SYNTAX BitFail
			MAX-ACCESS read-only
			STATUS current
			DESCRIPTION
				"Indicates that the modules has an invalid almanac"
		::= { gps3000p02v3Entry 33 }

		-- 1.3.6.1.4.1.10106.3.101291.1.1.35
		gps3000p02v3GpsModFail OBJECT-TYPE
			SYNTAX BitFail
			MAX-ACCESS read-only
			STATUS current
			DESCRIPTION
				"Indicates that an error has been detected in the GPS receiver module"
		::= { gps3000p02v3Entry 35 }

		-- 1.3.6.1.4.1.10106.3.101291.1.1.37
		gps3000p02v3GpsTrackSats OBJECT-TYPE
			SYNTAX GpsSatellites
			MAX-ACCESS read-only
			STATUS current
			DESCRIPTION
				"Number of GPS tracking satellites"
		::= { gps3000p02v3Entry 37 }

		-- 1.3.6.1.4.1.10106.3.101291.1.1.39
		gps3000p02v3GpsVisibleSats OBJECT-TYPE
			SYNTAX GpsSatellites
			MAX-ACCESS read-only
			STATUS current
			DESCRIPTION
				"Number of GPS visible satellites"
		::= { gps3000p02v3Entry 39 }

		-- 1.3.6.1.4.1.10106.3.101291.1.1.41
		gps3000p02v3GpsSignalLevel OBJECT-TYPE
			SYNTAX LevelDbHz
			MAX-ACCESS read-only
			STATUS current
			DESCRIPTION
				"Estimated carrier to noise ratio for the best satellite in tracking"
		::= { gps3000p02v3Entry 41 }

		-- 1.3.6.1.4.1.10106.3.101291.1.1.43
		gps3000p02v3AdquisitionStat OBJECT-TYPE
			SYNTAX GpsAdqStat1
			MAX-ACCESS read-only
			STATUS current
			DESCRIPTION
				"GPS3000 module adquisition status"
		::= { gps3000p02v3Entry 43 }

		-- 1.3.6.1.4.1.10106.3.101291.1.1.45
		gps3000p02v3HoldoverTime OBJECT-TYPE
			SYNTAX GpsHoldovrTime
			MAX-ACCESS read-only
			STATUS current
			DESCRIPTION
				"Holdover time"
		::= { gps3000p02v3Entry 45 }

		-- 1.3.6.1.4.1.10106.3.101291.1.1.47
		gps3000p02v3FreqDriftEst OBJECT-TYPE
			SYNTAX GpsFrqDrftEst
			MAX-ACCESS read-only
			STATUS current
			DESCRIPTION
				"Frequency drift estimation"
		::= { gps3000p02v3Entry 47 }

		-- 1.3.6.1.4.1.10106.3.101291.1.1.49
		gps3000p02v3PhaseDriftEst OBJECT-TYPE
			SYNTAX GpsPhsDrftEst
			MAX-ACCESS read-only
			STATUS current
			DESCRIPTION
				"Phase drift estimation"
		::= { gps3000p02v3Entry 49 }

		-- 1.3.6.1.4.1.10106.3.213204
		gps3000p02v4 OBJECT IDENTIFIER ::= { albalaProducts 213204 }

		-- 1.3.6.1.4.1.10106.3.213204.1
		gps3000p02v4Table  OBJECT-TYPE
			SYNTAX SEQUENCE OF Gps3000p02v4Entry
			MAX-ACCESS not-accessible
			STATUS current
			DESCRIPTION
				"Module  GPS3000P02V4 Table"
			::= { gps3000p02v4 1 }

		-- 1.3.6.1.4.1.10106.3.213204.1.1
		gps3000p02v4Entry  OBJECT-TYPE
			SYNTAX Gps3000p02v4Entry
			MAX-ACCESS not-accessible
			STATUS current
			DESCRIPTION
				"Module GPS3000P02V4 Entry"
			INDEX { gps3000p02v4Index }
			::= { gps3000p02v4Table 1 }

			Gps3000p02v4Entry ::=
			SEQUENCE {
				gps3000p02v4Index
				ModuleIndex,
				gps3000p02v4Holdover
				Bit0Dis1Ena,
				gps3000p02v4HoldoverTrapEnable
				AlarmEnable,
				gps3000p02v4CableDelay
				DelayX2Ns,
				gps3000p02v4VideoOut
				Bit05251625,
				gps3000p02v4SdiVidHDelay
				DelayPixel1,
				gps3000p02v4SdiVidVDelay
				DelayLines1,
				gps3000p02v4SdiVidFrDelay
				DelayFram1,
				gps3000p02v4AnaVidHDelay
				DelayPixel2,
				gps3000p02v4VitcInsLine
				VideoLine,
				gps3000p02v4AnaVidSch
				Sch1,
				gps3000p02v4HoldoverStat
				Bit0Trk1Hol,
				gps3000p02v4HoldoverStatTrapEnable
				AlarmEnable,
				gps3000p02v4RedundFail
				BitFail,
				gps3000p02v4RedundFailTrapEnable
				AlarmEnable,
				gps3000p02v4OutputsMuted
				BitFail,
				gps3000p02v4OutputsMutedTrapEnable
				AlarmEnable,
				gps3000p02v4SatRxStat
				GpsSatRxStat,
				gps3000p02v4AntenaStat
				GpsAntenaStat,
				gps3000p02v4AntenaStatTrapEnable
				AlarmEnable,
				gps3000p02v4SatNoFail
				BitFail,
				gps3000p02v4AlmanacFail
				BitFail,
				gps3000p02v4GpsModFail
				BitFail,
				gps3000p02v4GpsTrackSats
				GpsSatellites,
				gps3000p02v4GpsVisibleSats
				GpsSatellites,
				gps3000p02v4GpsSignalLevel
				LevelDbHz,
				gps3000p02v4AdquisitionStat
				GpsAdqStat1,
				gps3000p02v4HoldoverTime
				GpsHoldovrTime,
				gps3000p02v4FreqDriftEst
				GpsFrqDrftEst,
				gps3000p02v4PhaseDriftEst
				GpsPhsDrftEst
			 }

		-- 1.3.6.1.4.1.10106.3.101291.1.1.1
		gps3000p02v4Index OBJECT-TYPE
			SYNTAX ModuleIndex
			MAX-ACCESS read-only
			STATUS current
			DESCRIPTION
				"Index of GPS3000P02V4 Table"
		::= { gps3000p02v4Entry 1 }

		-- 1.3.6.1.4.1.10106.3.101291.1.1.3
		gps3000p02v4Holdover OBJECT-TYPE
			SYNTAX Bit0Dis1Ena
			MAX-ACCESS read-write
			STATUS current
			DESCRIPTION
				"Allows setting the module in the holdover mode"
		::= { gps3000p02v4Entry 3 }

		-- 1.3.6.1.4.1.10106.3.101291.1.1.4
		gps3000p02v4HoldoverTrapEnable OBJECT-TYPE
			SYNTAX AlarmEnable
			MAX-ACCESS read-write
			STATUS current
			DESCRIPTION
				"Allows setting the module in the holdover mode Trap Enable"
		::= { gps3000p02v4Entry 4 }

		-- 1.3.6.1.4.1.10106.3.101291.1.1.5
		gps3000p02v4CableDelay OBJECT-TYPE
			SYNTAX DelayX2Ns
			MAX-ACCESS read-write
			STATUS current
			DESCRIPTION
				"Allows compensating the antenna cable delay"
		::= { gps3000p02v4Entry 5 }

		-- 1.3.6.1.4.1.10106.3.101291.1.1.7
		gps3000p02v4VideoOut OBJECT-TYPE
			SYNTAX Bit05251625
			MAX-ACCESS read-only
			STATUS current
			DESCRIPTION
				"Allows selecting the video output format"
		::= { gps3000p02v4Entry 7 }

		-- 1.3.6.1.4.1.10106.3.101291.1.1.9
		gps3000p02v4SdiVidHDelay OBJECT-TYPE
			SYNTAX DelayPixel1
			MAX-ACCESS read-write
			STATUS current
			DESCRIPTION
				"Allows adjusting the SDI video horizontal delay"
		::= { gps3000p02v4Entry 9 }

		-- 1.3.6.1.4.1.10106.3.101291.1.1.11
		gps3000p02v4SdiVidVDelay OBJECT-TYPE
			SYNTAX DelayLines1
			MAX-ACCESS read-write
			STATUS current
			DESCRIPTION
				"Allows adjusting the SDI video vertical delay"
		::= { gps3000p02v4Entry 11 }

		-- 1.3.6.1.4.1.10106.3.101291.1.1.13
		gps3000p02v4SdiVidFrDelay OBJECT-TYPE
			SYNTAX DelayFram1
			MAX-ACCESS read-write
			STATUS current
			DESCRIPTION
				"Allows adjusting the SDI video frame delay"
		::= { gps3000p02v4Entry 13 }

		-- 1.3.6.1.4.1.10106.3.101291.1.1.15
		gps3000p02v4AnaVidHDelay OBJECT-TYPE
			SYNTAX DelayPixel2
			MAX-ACCESS read-write
			STATUS current
			DESCRIPTION
				"Allows adjusting the Analog to SDI video horizontal delay"
		::= { gps3000p02v4Entry 15 }

		-- 1.3.6.1.4.1.10106.3.101291.1.1.17
		gps3000p02v4VitcInsLine OBJECT-TYPE
			SYNTAX VideoLine
			MAX-ACCESS read-write
			STATUS current
			DESCRIPTION
				"Allows adjusting the VITC insertion line"
		::= { gps3000p02v4Entry 17 }

		-- 1.3.6.1.4.1.10106.3.101291.1.1.19
		gps3000p02v4AnaVidSch OBJECT-TYPE
			SYNTAX Sch1
			MAX-ACCESS read-write
			STATUS current
			DESCRIPTION
				"Allows adjusting the Analog video SCH"
		::= { gps3000p02v4Entry 19 }

		-- 1.3.6.1.4.1.10106.3.101291.1.1.21
		gps3000p02v4HoldoverStat OBJECT-TYPE
			SYNTAX Bit0Trk1Hol
			MAX-ACCESS read-only
			STATUS current
			DESCRIPTION
				"Indicates if the module is locked to GPS or to reference or it is in holdover mode"
		::= { gps3000p02v4Entry 21 }

		-- 1.3.6.1.4.1.10106.3.101291.1.1.22
		gps3000p02v4HoldoverStatTrapEnable OBJECT-TYPE
			SYNTAX AlarmEnable
			MAX-ACCESS read-write
			STATUS current
			DESCRIPTION
				"Indicates if the module is locked to GPS or to reference or it is in holdover mode Trap Enable"
		::= { gps3000p02v4Entry 22 }

		-- 1.3.6.1.4.1.10106.3.101291.1.1.23
		gps3000p02v4RedundFail OBJECT-TYPE
			SYNTAX BitFail
			MAX-ACCESS read-only
			STATUS current
			DESCRIPTION
				"Indicates if there is any active module in the redundance system"
		::= { gps3000p02v4Entry 23 }

		-- 1.3.6.1.4.1.10106.3.101291.1.1.24
		gps3000p02v4RedundFailTrapEnable OBJECT-TYPE
			SYNTAX AlarmEnable
			MAX-ACCESS read-write
			STATUS current
			DESCRIPTION
				"Indicates if there is any active module in the redundance system Trap Enable"
		::= { gps3000p02v4Entry 24 }

		-- 1.3.6.1.4.1.10106.3.101291.1.1.25
		gps3000p02v4OutputsMuted OBJECT-TYPE
			SYNTAX BitFail
			MAX-ACCESS read-only
			STATUS current
			DESCRIPTION
				"Indicates f the module outputs are active"
		::= { gps3000p02v4Entry 25 }

		-- 1.3.6.1.4.1.10106.3.101291.1.1.26
		gps3000p02v4OutputsMutedTrapEnable OBJECT-TYPE
			SYNTAX AlarmEnable
			MAX-ACCESS read-write
			STATUS current
			DESCRIPTION
				"Indicates f the module outputs are active Trap Enable"
		::= { gps3000p02v4Entry 26 }

		-- 1.3.6.1.4.1.10106.3.101291.1.1.27
		gps3000p02v4SatRxStat OBJECT-TYPE
			SYNTAX GpsSatRxStat
			MAX-ACCESS read-only
			STATUS current
			DESCRIPTION
				"GPS receiver module satellite tracking status"
		::= { gps3000p02v4Entry 27 }

		-- 1.3.6.1.4.1.10106.3.101291.1.1.29
		gps3000p02v4AntenaStat OBJECT-TYPE
			SYNTAX GpsAntenaStat
			MAX-ACCESS read-only
			STATUS current
			DESCRIPTION
				"Antenna connection status"
		::= { gps3000p02v4Entry 29 }

		-- 1.3.6.1.4.1.10106.3.101291.1.1.30
		gps3000p02v4AntenaStatTrapEnable OBJECT-TYPE
			SYNTAX AlarmEnable
			MAX-ACCESS read-write
			STATUS current
			DESCRIPTION
				"Antenna connection status Trap Enable"
		::= { gps3000p02v4Entry 30 }

		-- 1.3.6.1.4.1.10106.3.101291.1.1.31
		gps3000p02v4SatNoFail OBJECT-TYPE
			SYNTAX BitFail
			MAX-ACCESS read-only
			STATUS current
			DESCRIPTION
				"Indicates that the number of visible satellites is low"
		::= { gps3000p02v4Entry 31 }

		-- 1.3.6.1.4.1.10106.3.101291.1.1.33
		gps3000p02v4AlmanacFail OBJECT-TYPE
			SYNTAX BitFail
			MAX-ACCESS read-only
			STATUS current
			DESCRIPTION
				"Indicates that the modules has an invalid almanac"
		::= { gps3000p02v4Entry 33 }

		-- 1.3.6.1.4.1.10106.3.101291.1.1.35
		gps3000p02v4GpsModFail OBJECT-TYPE
			SYNTAX BitFail
			MAX-ACCESS read-only
			STATUS current
			DESCRIPTION
				"Indicates that an error has been detected in the GPS receiver module"
		::= { gps3000p02v4Entry 35 }

		-- 1.3.6.1.4.1.10106.3.101291.1.1.37
		gps3000p02v4GpsTrackSats OBJECT-TYPE
			SYNTAX GpsSatellites
			MAX-ACCESS read-only
			STATUS current
			DESCRIPTION
				"Number of GPS tracking satellites"
		::= { gps3000p02v4Entry 37 }

		-- 1.3.6.1.4.1.10106.3.101291.1.1.39
		gps3000p02v4GpsVisibleSats OBJECT-TYPE
			SYNTAX GpsSatellites
			MAX-ACCESS read-only
			STATUS current
			DESCRIPTION
				"Number of GPS visible satellites"
		::= { gps3000p02v4Entry 39 }

		-- 1.3.6.1.4.1.10106.3.101291.1.1.41
		gps3000p02v4GpsSignalLevel OBJECT-TYPE
			SYNTAX LevelDbHz
			MAX-ACCESS read-only
			STATUS current
			DESCRIPTION
				"Estimated carrier to noise ratio for the best satellite in tracking"
		::= { gps3000p02v4Entry 41 }

		-- 1.3.6.1.4.1.10106.3.101291.1.1.43
		gps3000p02v4AdquisitionStat OBJECT-TYPE
			SYNTAX GpsAdqStat1
			MAX-ACCESS read-only
			STATUS current
			DESCRIPTION
				"GPS3000 module adquisition status"
		::= { gps3000p02v4Entry 43 }

		-- 1.3.6.1.4.1.10106.3.101291.1.1.45
		gps3000p02v4HoldoverTime OBJECT-TYPE
			SYNTAX GpsHoldovrTime
			MAX-ACCESS read-only
			STATUS current
			DESCRIPTION
				"Holdover time"
		::= { gps3000p02v4Entry 45 }

		-- 1.3.6.1.4.1.10106.3.101291.1.1.47
		gps3000p02v4FreqDriftEst OBJECT-TYPE
			SYNTAX GpsFrqDrftEst
			MAX-ACCESS read-only
			STATUS current
			DESCRIPTION
				"Frequency drift estimation"
		::= { gps3000p02v4Entry 47 }

		-- 1.3.6.1.4.1.10106.3.101291.1.1.49
		gps3000p02v4PhaseDriftEst OBJECT-TYPE
			SYNTAX GpsPhsDrftEst
			MAX-ACCESS read-only
			STATUS current
			DESCRIPTION
				"Phase drift estimation"
		::= { gps3000p02v4Entry 49 }

		-- 1.3.6.1.4.1.10106.3.215401
		pds3001p01v1 OBJECT IDENTIFIER ::= { albalaProducts 215401 }

		-- 1.3.6.1.4.1.10106.3.215401.1
		pds3001p01v1Table  OBJECT-TYPE
			SYNTAX SEQUENCE OF Pds3001p01v1Entry
			MAX-ACCESS not-accessible
			STATUS current
			DESCRIPTION
				"Module  PDS3001P01V1 Table"
			::= { pds3001p01v1 1 }

		-- 1.3.6.1.4.1.10106.3.215401.1.1
		pds3001p01v1Entry  OBJECT-TYPE
			SYNTAX Pds3001p01v1Entry
			MAX-ACCESS not-accessible
			STATUS current
			DESCRIPTION
				"Module PDS3001P01V1 Entry"
			INDEX { pds3001p01v1Index }
			::= { pds3001p01v1Table 1 }

			Pds3001p01v1Entry ::=
			SEQUENCE {
				pds3001p01v1Index
				ModuleIndex,
				pds3001p01v1BlackLevel
				Uint8,
				pds3001p01v1MeanDispThres
				Uint8,
				pds3001p01v1PeakDispThres
				Uint8,
				pds3001p01v1BlckTimeout
				Uint8,
				pds3001p01v1FreezeTimeout
				Uint8,
				pds3001p01v1UnlockMask
				BitMask,
				pds3001p01v1BlackMask
				BitMask,
				pds3001p01v1PeakFreezeMask
				BitMask,
				pds3001p01v1MeanFreezeMask
				BitMask,
				pds3001p01v1Gpo1MskUnlock
				BitMask,
				pds3001p01v1Gpo1MskBlack
				BitMask,
				pds3001p01v1Gpo1MskFreeze
				BitMask,
				pds3001p01v1Gpo2MskUnlock
				BitMask,
				pds3001p01v1Gpo2MskBlack
				BitMask,
				pds3001p01v1Gpo2MskFreeze
				BitMask,
				pds3001p01v1Unlock
				BitFail,
				pds3001p01v1UnlockTrapEnable
				AlarmEnable,
				pds3001p01v1Black
				BitFail,
				pds3001p01v1BlackTrapEnable
				AlarmEnable,
				pds3001p01v1Freeze
				BitFail,
				pds3001p01v1FreezeTrapEnable
				AlarmEnable,
				pds3001p01v1UnlockT
				BitFail,
				pds3001p01v1UnlockTTrapEnable
				AlarmEnable,
				pds3001p01v1BlackT
				BitFail,
				pds3001p01v1BlackTTrapEnable
				AlarmEnable,
				pds3001p01v1FreezeT
				BitFail,
				pds3001p01v1FreezeTTrapEnable
				AlarmEnable,
				pds3001p01v1Overload
				BitFail,
				pds3001p01v1OverloadTrapEnable
				AlarmEnable
			 }

		-- 1.3.6.1.4.1.10106.3.101291.1.1.1
		pds3001p01v1Index OBJECT-TYPE
			SYNTAX ModuleIndex
			MAX-ACCESS read-only
			STATUS current
			DESCRIPTION
				"Index of PDS3001P01V1 Table"
		::= { pds3001p01v1Entry 1 }

		-- 1.3.6.1.4.1.10106.3.101291.1.1.3
		pds3001p01v1BlackLevel OBJECT-TYPE
			SYNTAX Uint8
			MAX-ACCESS read-write
			STATUS current
			DESCRIPTION
				"Allows adjusting the black level"
		::= { pds3001p01v1Entry 3 }

		-- 1.3.6.1.4.1.10106.3.101291.1.1.5
		pds3001p01v1MeanDispThres OBJECT-TYPE
			SYNTAX Uint8
			MAX-ACCESS read-write
			STATUS current
			DESCRIPTION
				"Allows adjusting freeze mean disparity threshold"
		::= { pds3001p01v1Entry 5 }

		-- 1.3.6.1.4.1.10106.3.101291.1.1.7
		pds3001p01v1PeakDispThres OBJECT-TYPE
			SYNTAX Uint8
			MAX-ACCESS read-write
			STATUS current
			DESCRIPTION
				"Allows adjusting freeze peak disparity threshold"
		::= { pds3001p01v1Entry 7 }

		-- 1.3.6.1.4.1.10106.3.101291.1.1.9
		pds3001p01v1BlckTimeout OBJECT-TYPE
			SYNTAX Uint8
			MAX-ACCESS read-write
			STATUS current
			DESCRIPTION
				"Allows selecting the black fail detection timeout"
		::= { pds3001p01v1Entry 9 }

		-- 1.3.6.1.4.1.10106.3.101291.1.1.11
		pds3001p01v1FreezeTimeout OBJECT-TYPE
			SYNTAX Uint8
			MAX-ACCESS read-write
			STATUS current
			DESCRIPTION
				"Allows selecting the freeze fail detection timeout"
		::= { pds3001p01v1Entry 11 }

		-- 1.3.6.1.4.1.10106.3.101291.1.1.13
		pds3001p01v1UnlockMask OBJECT-TYPE
			SYNTAX BitMask
			MAX-ACCESS read-write
			STATUS current
			DESCRIPTION
				"Allows masking unlock fail"
		::= { pds3001p01v1Entry 13 }

		-- 1.3.6.1.4.1.10106.3.101291.1.1.15
		pds3001p01v1BlackMask OBJECT-TYPE
			SYNTAX BitMask
			MAX-ACCESS read-write
			STATUS current
			DESCRIPTION
				"Allows masking the black pattern fail"
		::= { pds3001p01v1Entry 15 }

		-- 1.3.6.1.4.1.10106.3.101291.1.1.17
		pds3001p01v1PeakFreezeMask OBJECT-TYPE
			SYNTAX BitMask
			MAX-ACCESS read-write
			STATUS current
			DESCRIPTION
				"Allows masking the freeze image fail (peak detection)"
		::= { pds3001p01v1Entry 17 }

		-- 1.3.6.1.4.1.10106.3.101291.1.1.19
		pds3001p01v1MeanFreezeMask OBJECT-TYPE
			SYNTAX BitMask
			MAX-ACCESS read-write
			STATUS current
			DESCRIPTION
				"Allows masking the freeze image fail (mean detection)"
		::= { pds3001p01v1Entry 19 }

		-- 1.3.6.1.4.1.10106.3.101291.1.1.21
		pds3001p01v1Gpo1MskUnlock OBJECT-TYPE
			SYNTAX BitMask
			MAX-ACCESS read-write
			STATUS current
			DESCRIPTION
				"Selects if GPO1 activates when input unlocks"
		::= { pds3001p01v1Entry 21 }

		-- 1.3.6.1.4.1.10106.3.101291.1.1.23
		pds3001p01v1Gpo1MskBlack OBJECT-TYPE
			SYNTAX BitMask
			MAX-ACCESS read-write
			STATUS current
			DESCRIPTION
				"Selects if GPO1 activates when input is black"
		::= { pds3001p01v1Entry 23 }

		-- 1.3.6.1.4.1.10106.3.101291.1.1.25
		pds3001p01v1Gpo1MskFreeze OBJECT-TYPE
			SYNTAX BitMask
			MAX-ACCESS read-write
			STATUS current
			DESCRIPTION
				"Selects if GPO1 activates when input is freeze"
		::= { pds3001p01v1Entry 25 }

		-- 1.3.6.1.4.1.10106.3.101291.1.1.27
		pds3001p01v1Gpo2MskUnlock OBJECT-TYPE
			SYNTAX BitMask
			MAX-ACCESS read-write
			STATUS current
			DESCRIPTION
				"Selects if GPO2 activates when input unlocks"
		::= { pds3001p01v1Entry 27 }

		-- 1.3.6.1.4.1.10106.3.101291.1.1.29
		pds3001p01v1Gpo2MskBlack OBJECT-TYPE
			SYNTAX BitMask
			MAX-ACCESS read-write
			STATUS current
			DESCRIPTION
				"Selects if GPO2 activates when input is black"
		::= { pds3001p01v1Entry 29 }

		-- 1.3.6.1.4.1.10106.3.101291.1.1.31
		pds3001p01v1Gpo2MskFreeze OBJECT-TYPE
			SYNTAX BitMask
			MAX-ACCESS read-write
			STATUS current
			DESCRIPTION
				"Selects if GPO2 activates when input is freeze"
		::= { pds3001p01v1Entry 31 }

		-- 1.3.6.1.4.1.10106.3.101291.1.1.33
		pds3001p01v1Unlock OBJECT-TYPE
			SYNTAX BitFail
			MAX-ACCESS read-only
			STATUS current
			DESCRIPTION
				"Indicates signal unlock fail"
		::= { pds3001p01v1Entry 33 }

		-- 1.3.6.1.4.1.10106.3.101291.1.1.34
		pds3001p01v1UnlockTrapEnable OBJECT-TYPE
			SYNTAX AlarmEnable
			MAX-ACCESS read-write
			STATUS current
			DESCRIPTION
				"Indicates signal unlock fail Trap Enable"
		::= { pds3001p01v1Entry 34 }

		-- 1.3.6.1.4.1.10106.3.101291.1.1.35
		pds3001p01v1Black OBJECT-TYPE
			SYNTAX BitFail
			MAX-ACCESS read-only
			STATUS current
			DESCRIPTION
				"Indicates black pattern instantaneous fail"
		::= { pds3001p01v1Entry 35 }

		-- 1.3.6.1.4.1.10106.3.101291.1.1.36
		pds3001p01v1BlackTrapEnable OBJECT-TYPE
			SYNTAX AlarmEnable
			MAX-ACCESS read-write
			STATUS current
			DESCRIPTION
				"Indicates black pattern instantaneous fail Trap Enable"
		::= { pds3001p01v1Entry 36 }

		-- 1.3.6.1.4.1.10106.3.101291.1.1.37
		pds3001p01v1Freeze OBJECT-TYPE
			SYNTAX BitFail
			MAX-ACCESS read-only
			STATUS current
			DESCRIPTION
				"Indicates freeze image instantaneous fail"
		::= { pds3001p01v1Entry 37 }

		-- 1.3.6.1.4.1.10106.3.101291.1.1.38
		pds3001p01v1FreezeTrapEnable OBJECT-TYPE
			SYNTAX AlarmEnable
			MAX-ACCESS read-write
			STATUS current
			DESCRIPTION
				"Indicates freeze image instantaneous fail Trap Enable"
		::= { pds3001p01v1Entry 38 }

		-- 1.3.6.1.4.1.10106.3.101291.1.1.39
		pds3001p01v1UnlockT OBJECT-TYPE
			SYNTAX BitFail
			MAX-ACCESS read-only
			STATUS current
			DESCRIPTION
				"Indicates unlock filtered fail"
		::= { pds3001p01v1Entry 39 }

		-- 1.3.6.1.4.1.10106.3.101291.1.1.40
		pds3001p01v1UnlockTTrapEnable OBJECT-TYPE
			SYNTAX AlarmEnable
			MAX-ACCESS read-write
			STATUS current
			DESCRIPTION
				"Indicates unlock filtered fail Trap Enable"
		::= { pds3001p01v1Entry 40 }

		-- 1.3.6.1.4.1.10106.3.101291.1.1.41
		pds3001p01v1BlackT OBJECT-TYPE
			SYNTAX BitFail
			MAX-ACCESS read-only
			STATUS current
			DESCRIPTION
				"Indicates black pattern filtered fail"
		::= { pds3001p01v1Entry 41 }

		-- 1.3.6.1.4.1.10106.3.101291.1.1.42
		pds3001p01v1BlackTTrapEnable OBJECT-TYPE
			SYNTAX AlarmEnable
			MAX-ACCESS read-write
			STATUS current
			DESCRIPTION
				"Indicates black pattern filtered fail Trap Enable"
		::= { pds3001p01v1Entry 42 }

		-- 1.3.6.1.4.1.10106.3.101291.1.1.43
		pds3001p01v1FreezeT OBJECT-TYPE
			SYNTAX BitFail
			MAX-ACCESS read-only
			STATUS current
			DESCRIPTION
				"Indicates freeze image filtered fail"
		::= { pds3001p01v1Entry 43 }

		-- 1.3.6.1.4.1.10106.3.101291.1.1.44
		pds3001p01v1FreezeTTrapEnable OBJECT-TYPE
			SYNTAX AlarmEnable
			MAX-ACCESS read-write
			STATUS current
			DESCRIPTION
				"Indicates freeze image filtered fail Trap Enable"
		::= { pds3001p01v1Entry 44 }

		-- 1.3.6.1.4.1.10106.3.101291.1.1.45
		pds3001p01v1Overload OBJECT-TYPE
			SYNTAX BitFail
			MAX-ACCESS read-only
			STATUS current
			DESCRIPTION
				"Indicates the that the input level is too high"
		::= { pds3001p01v1Entry 45 }

		-- 1.3.6.1.4.1.10106.3.101291.1.1.46
		pds3001p01v1OverloadTrapEnable OBJECT-TYPE
			SYNTAX AlarmEnable
			MAX-ACCESS read-write
			STATUS current
			DESCRIPTION
				"Indicates the that the input level is too high Trap Enable"
		::= { pds3001p01v1Entry 46 }

		-- 1.3.6.1.4.1.10106.3.216401
		gps3000p03v1 OBJECT IDENTIFIER ::= { albalaProducts 216401 }

		-- 1.3.6.1.4.1.10106.3.216401.1
		gps3000p03v1Table  OBJECT-TYPE
			SYNTAX SEQUENCE OF Gps3000p03v1Entry
			MAX-ACCESS not-accessible
			STATUS current
			DESCRIPTION
				"Module  GPS3000P03V1 Table"
			::= { gps3000p03v1 1 }

		-- 1.3.6.1.4.1.10106.3.216401.1.1
		gps3000p03v1Entry  OBJECT-TYPE
			SYNTAX Gps3000p03v1Entry
			MAX-ACCESS not-accessible
			STATUS current
			DESCRIPTION
				"Module GPS3000P03V1 Entry"
			INDEX { gps3000p03v1Index }
			::= { gps3000p03v1Table 1 }

			Gps3000p03v1Entry ::=
			SEQUENCE {
				gps3000p03v1Index
				ModuleIndex,
				gps3000p03v1Holdover
				Bit0Dis1Ena,
				gps3000p03v1HoldoverTrapEnable
				AlarmEnable,
				gps3000p03v1CableDelay
				DelayX2Ns,
				gps3000p03v1VideoOut
				Bit05251625,
				gps3000p03v1SdiVidHDelay
				DelayPixel1,
				gps3000p03v1SdiVidVDelay
				DelayLines1,
				gps3000p03v1SdiVidFrDelay
				DelayFram1,
				gps3000p03v1AnaVidHDelay
				DelayPixel2,
				gps3000p03v1VitcInsLine
				VideoLine,
				gps3000p03v1AnaVidSch
				Sch1,
				gps3000p03v1HoldoverStat
				Bit0Trk1Hol,
				gps3000p03v1HoldoverStatTrapEnable
				AlarmEnable,
				gps3000p03v1RedundFail
				BitFail,
				gps3000p03v1RedundFailTrapEnable
				AlarmEnable,
				gps3000p03v1OutputsMuted
				BitFail,
				gps3000p03v1OutputsMutedTrapEnable
				AlarmEnable,
				gps3000p03v1SatRxStat
				GpsSatRxStat,
				gps3000p03v1AntenaStat
				GpsAntenaStat,
				gps3000p03v1AntenaStatTrapEnable
				AlarmEnable,
				gps3000p03v1SatNoFail
				BitFail,
				gps3000p03v1AlmanacFail
				BitFail,
				gps3000p03v1GpsModFail
				BitFail,
				gps3000p03v1GpsTrackSats
				GpsSatellites,
				gps3000p03v1GpsVisibleSats
				GpsSatellites,
				gps3000p03v1GpsSignalLevel
				LevelDbHz,
				gps3000p03v1AdquisitionStat
				GpsAdqStat1,
				gps3000p03v1HoldoverTime
				GpsHoldovrTime,
				gps3000p03v1FreqDriftEst
				GpsFrqDrftEst,
				gps3000p03v1PhaseDriftEst
				GpsPhsDrftEst
			 }

		-- 1.3.6.1.4.1.10106.3.101291.1.1.1
		gps3000p03v1Index OBJECT-TYPE
			SYNTAX ModuleIndex
			MAX-ACCESS read-only
			STATUS current
			DESCRIPTION
				"Index of GPS3000P03V1 Table"
		::= { gps3000p03v1Entry 1 }

		-- 1.3.6.1.4.1.10106.3.101291.1.1.3
		gps3000p03v1Holdover OBJECT-TYPE
			SYNTAX Bit0Dis1Ena
			MAX-ACCESS read-write
			STATUS current
			DESCRIPTION
				"Allows setting the module in the holdover mode"
		::= { gps3000p03v1Entry 3 }

		-- 1.3.6.1.4.1.10106.3.101291.1.1.4
		gps3000p03v1HoldoverTrapEnable OBJECT-TYPE
			SYNTAX AlarmEnable
			MAX-ACCESS read-write
			STATUS current
			DESCRIPTION
				"Allows setting the module in the holdover mode Trap Enable"
		::= { gps3000p03v1Entry 4 }

		-- 1.3.6.1.4.1.10106.3.101291.1.1.5
		gps3000p03v1CableDelay OBJECT-TYPE
			SYNTAX DelayX2Ns
			MAX-ACCESS read-write
			STATUS current
			DESCRIPTION
				"Allows compensating the antenna cable delay"
		::= { gps3000p03v1Entry 5 }

		-- 1.3.6.1.4.1.10106.3.101291.1.1.7
		gps3000p03v1VideoOut OBJECT-TYPE
			SYNTAX Bit05251625
			MAX-ACCESS read-only
			STATUS current
			DESCRIPTION
				"Allows selecting the video output format"
		::= { gps3000p03v1Entry 7 }

		-- 1.3.6.1.4.1.10106.3.101291.1.1.9
		gps3000p03v1SdiVidHDelay OBJECT-TYPE
			SYNTAX DelayPixel1
			MAX-ACCESS read-write
			STATUS current
			DESCRIPTION
				"Allows adjusting the SDI video horizontal delay"
		::= { gps3000p03v1Entry 9 }

		-- 1.3.6.1.4.1.10106.3.101291.1.1.11
		gps3000p03v1SdiVidVDelay OBJECT-TYPE
			SYNTAX DelayLines1
			MAX-ACCESS read-write
			STATUS current
			DESCRIPTION
				"Allows adjusting the SDI video vertical delay"
		::= { gps3000p03v1Entry 11 }

		-- 1.3.6.1.4.1.10106.3.101291.1.1.13
		gps3000p03v1SdiVidFrDelay OBJECT-TYPE
			SYNTAX DelayFram1
			MAX-ACCESS read-write
			STATUS current
			DESCRIPTION
				"Allows adjusting the SDI video frame delay"
		::= { gps3000p03v1Entry 13 }

		-- 1.3.6.1.4.1.10106.3.101291.1.1.15
		gps3000p03v1AnaVidHDelay OBJECT-TYPE
			SYNTAX DelayPixel2
			MAX-ACCESS read-write
			STATUS current
			DESCRIPTION
				"Allows adjusting the Analog to SDI video horizontal delay"
		::= { gps3000p03v1Entry 15 }

		-- 1.3.6.1.4.1.10106.3.101291.1.1.17
		gps3000p03v1VitcInsLine OBJECT-TYPE
			SYNTAX VideoLine
			MAX-ACCESS read-write
			STATUS current
			DESCRIPTION
				"Allows adjusting the VITC insertion line"
		::= { gps3000p03v1Entry 17 }

		-- 1.3.6.1.4.1.10106.3.101291.1.1.19
		gps3000p03v1AnaVidSch OBJECT-TYPE
			SYNTAX Sch1
			MAX-ACCESS read-write
			STATUS current
			DESCRIPTION
				"Allows adjusting the Analog video SCH"
		::= { gps3000p03v1Entry 19 }

		-- 1.3.6.1.4.1.10106.3.101291.1.1.21
		gps3000p03v1HoldoverStat OBJECT-TYPE
			SYNTAX Bit0Trk1Hol
			MAX-ACCESS read-only
			STATUS current
			DESCRIPTION
				"Indicates if the module is locked to GPS or to reference or it is in holdover mode"
		::= { gps3000p03v1Entry 21 }

		-- 1.3.6.1.4.1.10106.3.101291.1.1.22
		gps3000p03v1HoldoverStatTrapEnable OBJECT-TYPE
			SYNTAX AlarmEnable
			MAX-ACCESS read-write
			STATUS current
			DESCRIPTION
				"Indicates if the module is locked to GPS or to reference or it is in holdover mode Trap Enable"
		::= { gps3000p03v1Entry 22 }

		-- 1.3.6.1.4.1.10106.3.101291.1.1.23
		gps3000p03v1RedundFail OBJECT-TYPE
			SYNTAX BitFail
			MAX-ACCESS read-only
			STATUS current
			DESCRIPTION
				"Indicates if there is any active module in the redundance system"
		::= { gps3000p03v1Entry 23 }

		-- 1.3.6.1.4.1.10106.3.101291.1.1.24
		gps3000p03v1RedundFailTrapEnable OBJECT-TYPE
			SYNTAX AlarmEnable
			MAX-ACCESS read-write
			STATUS current
			DESCRIPTION
				"Indicates if there is any active module in the redundance system Trap Enable"
		::= { gps3000p03v1Entry 24 }

		-- 1.3.6.1.4.1.10106.3.101291.1.1.25
		gps3000p03v1OutputsMuted OBJECT-TYPE
			SYNTAX BitFail
			MAX-ACCESS read-only
			STATUS current
			DESCRIPTION
				"Indicates f the module outputs are active"
		::= { gps3000p03v1Entry 25 }

		-- 1.3.6.1.4.1.10106.3.101291.1.1.26
		gps3000p03v1OutputsMutedTrapEnable OBJECT-TYPE
			SYNTAX AlarmEnable
			MAX-ACCESS read-write
			STATUS current
			DESCRIPTION
				"Indicates f the module outputs are active Trap Enable"
		::= { gps3000p03v1Entry 26 }

		-- 1.3.6.1.4.1.10106.3.101291.1.1.27
		gps3000p03v1SatRxStat OBJECT-TYPE
			SYNTAX GpsSatRxStat
			MAX-ACCESS read-only
			STATUS current
			DESCRIPTION
				"GPS receiver module satellite tracking status"
		::= { gps3000p03v1Entry 27 }

		-- 1.3.6.1.4.1.10106.3.101291.1.1.29
		gps3000p03v1AntenaStat OBJECT-TYPE
			SYNTAX GpsAntenaStat
			MAX-ACCESS read-only
			STATUS current
			DESCRIPTION
				"Antenna connection status"
		::= { gps3000p03v1Entry 29 }

		-- 1.3.6.1.4.1.10106.3.101291.1.1.30
		gps3000p03v1AntenaStatTrapEnable OBJECT-TYPE
			SYNTAX AlarmEnable
			MAX-ACCESS read-write
			STATUS current
			DESCRIPTION
				"Antenna connection status Trap Enable"
		::= { gps3000p03v1Entry 30 }

		-- 1.3.6.1.4.1.10106.3.101291.1.1.31
		gps3000p03v1SatNoFail OBJECT-TYPE
			SYNTAX BitFail
			MAX-ACCESS read-only
			STATUS current
			DESCRIPTION
				"Indicates that the number of visible satellites is low"
		::= { gps3000p03v1Entry 31 }

		-- 1.3.6.1.4.1.10106.3.101291.1.1.33
		gps3000p03v1AlmanacFail OBJECT-TYPE
			SYNTAX BitFail
			MAX-ACCESS read-only
			STATUS current
			DESCRIPTION
				"Indicates that the modules has an invalid almanac"
		::= { gps3000p03v1Entry 33 }

		-- 1.3.6.1.4.1.10106.3.101291.1.1.35
		gps3000p03v1GpsModFail OBJECT-TYPE
			SYNTAX BitFail
			MAX-ACCESS read-only
			STATUS current
			DESCRIPTION
				"Indicates that an error has been detected in the GPS receiver module"
		::= { gps3000p03v1Entry 35 }

		-- 1.3.6.1.4.1.10106.3.101291.1.1.37
		gps3000p03v1GpsTrackSats OBJECT-TYPE
			SYNTAX GpsSatellites
			MAX-ACCESS read-only
			STATUS current
			DESCRIPTION
				"Number of GPS tracking satellites"
		::= { gps3000p03v1Entry 37 }

		-- 1.3.6.1.4.1.10106.3.101291.1.1.39
		gps3000p03v1GpsVisibleSats OBJECT-TYPE
			SYNTAX GpsSatellites
			MAX-ACCESS read-only
			STATUS current
			DESCRIPTION
				"Number of GPS visible satellites"
		::= { gps3000p03v1Entry 39 }

		-- 1.3.6.1.4.1.10106.3.101291.1.1.41
		gps3000p03v1GpsSignalLevel OBJECT-TYPE
			SYNTAX LevelDbHz
			MAX-ACCESS read-only
			STATUS current
			DESCRIPTION
				"Estimated carrier to noise ratio for the best satellite in tracking"
		::= { gps3000p03v1Entry 41 }

		-- 1.3.6.1.4.1.10106.3.101291.1.1.43
		gps3000p03v1AdquisitionStat OBJECT-TYPE
			SYNTAX GpsAdqStat1
			MAX-ACCESS read-only
			STATUS current
			DESCRIPTION
				"GPS3000 module adquisition status"
		::= { gps3000p03v1Entry 43 }

		-- 1.3.6.1.4.1.10106.3.101291.1.1.45
		gps3000p03v1HoldoverTime OBJECT-TYPE
			SYNTAX GpsHoldovrTime
			MAX-ACCESS read-only
			STATUS current
			DESCRIPTION
				"Holdover time"
		::= { gps3000p03v1Entry 45 }

		-- 1.3.6.1.4.1.10106.3.101291.1.1.47
		gps3000p03v1FreqDriftEst OBJECT-TYPE
			SYNTAX GpsFrqDrftEst
			MAX-ACCESS read-only
			STATUS current
			DESCRIPTION
				"Frequency drift estimation"
		::= { gps3000p03v1Entry 47 }

		-- 1.3.6.1.4.1.10106.3.101291.1.1.49
		gps3000p03v1PhaseDriftEst OBJECT-TYPE
			SYNTAX GpsPhsDrftEst
			MAX-ACCESS read-only
			STATUS current
			DESCRIPTION
				"Phase drift estimation"
		::= { gps3000p03v1Entry 49 }

		-- 1.3.6.1.4.1.10106.3.216402
		gps3000p03v2 OBJECT IDENTIFIER ::= { albalaProducts 216402 }

		-- 1.3.6.1.4.1.10106.3.216402.1
		gps3000p03v2Table  OBJECT-TYPE
			SYNTAX SEQUENCE OF Gps3000p03v2Entry
			MAX-ACCESS not-accessible
			STATUS current
			DESCRIPTION
				"Module  GPS3000P03V2 Table"
			::= { gps3000p03v2 1 }

		-- 1.3.6.1.4.1.10106.3.216402.1.1
		gps3000p03v2Entry  OBJECT-TYPE
			SYNTAX Gps3000p03v2Entry
			MAX-ACCESS not-accessible
			STATUS current
			DESCRIPTION
				"Module GPS3000P03V2 Entry"
			INDEX { gps3000p03v2Index }
			::= { gps3000p03v2Table 1 }

			Gps3000p03v2Entry ::=
			SEQUENCE {
				gps3000p03v2Index
				ModuleIndex,
				gps3000p03v2Holdover
				Bit0Dis1Ena,
				gps3000p03v2HoldoverTrapEnable
				AlarmEnable,
				gps3000p03v2CableDelay
				DelayX2Ns,
				gps3000p03v2VideoOut
				Bit05251625,
				gps3000p03v2SdiVidHDelay
				DelayPixel1,
				gps3000p03v2SdiVidVDelay
				DelayLines1,
				gps3000p03v2SdiVidFrDelay
				DelayFram1,
				gps3000p03v2AnaVidHDelay
				DelayPixel2,
				gps3000p03v2VitcInsLine
				VideoLine,
				gps3000p03v2AnaVidSch
				Sch1,
				gps3000p03v2HoldoverStat
				Bit0Trk1Hol,
				gps3000p03v2HoldoverStatTrapEnable
				AlarmEnable,
				gps3000p03v2RedundFail
				BitFail,
				gps3000p03v2RedundFailTrapEnable
				AlarmEnable,
				gps3000p03v2OutputsMuted
				BitFail,
				gps3000p03v2OutputsMutedTrapEnable
				AlarmEnable,
				gps3000p03v2SatRxStat
				GpsSatRxStat,
				gps3000p03v2AntenaStat
				GpsAntenaStat,
				gps3000p03v2AntenaStatTrapEnable
				AlarmEnable,
				gps3000p03v2SatNoFail
				BitFail,
				gps3000p03v2AlmanacFail
				BitFail,
				gps3000p03v2GpsModFail
				BitFail,
				gps3000p03v2GpsTrackSats
				GpsSatellites,
				gps3000p03v2GpsVisibleSats
				GpsSatellites,
				gps3000p03v2GpsSignalLevel
				LevelDbHz,
				gps3000p03v2AdquisitionStat
				GpsAdqStat1,
				gps3000p03v2HoldoverTime
				GpsHoldovrTime,
				gps3000p03v2FreqDriftEst
				GpsFrqDrftEst,
				gps3000p03v2PhaseDriftEst
				GpsPhsDrftEst
			 }

		-- 1.3.6.1.4.1.10106.3.101291.1.1.1
		gps3000p03v2Index OBJECT-TYPE
			SYNTAX ModuleIndex
			MAX-ACCESS read-only
			STATUS current
			DESCRIPTION
				"Index of GPS3000P03V2 Table"
		::= { gps3000p03v2Entry 1 }

		-- 1.3.6.1.4.1.10106.3.101291.1.1.3
		gps3000p03v2Holdover OBJECT-TYPE
			SYNTAX Bit0Dis1Ena
			MAX-ACCESS read-write
			STATUS current
			DESCRIPTION
				"Allows setting the module in the holdover mode"
		::= { gps3000p03v2Entry 3 }

		-- 1.3.6.1.4.1.10106.3.101291.1.1.4
		gps3000p03v2HoldoverTrapEnable OBJECT-TYPE
			SYNTAX AlarmEnable
			MAX-ACCESS read-write
			STATUS current
			DESCRIPTION
				"Allows setting the module in the holdover mode Trap Enable"
		::= { gps3000p03v2Entry 4 }

		-- 1.3.6.1.4.1.10106.3.101291.1.1.5
		gps3000p03v2CableDelay OBJECT-TYPE
			SYNTAX DelayX2Ns
			MAX-ACCESS read-write
			STATUS current
			DESCRIPTION
				"Allows compensating the antenna cable delay"
		::= { gps3000p03v2Entry 5 }

		-- 1.3.6.1.4.1.10106.3.101291.1.1.7
		gps3000p03v2VideoOut OBJECT-TYPE
			SYNTAX Bit05251625
			MAX-ACCESS read-only
			STATUS current
			DESCRIPTION
				"Allows selecting the video output format"
		::= { gps3000p03v2Entry 7 }

		-- 1.3.6.1.4.1.10106.3.101291.1.1.9
		gps3000p03v2SdiVidHDelay OBJECT-TYPE
			SYNTAX DelayPixel1
			MAX-ACCESS read-write
			STATUS current
			DESCRIPTION
				"Allows adjusting the SDI video horizontal delay"
		::= { gps3000p03v2Entry 9 }

		-- 1.3.6.1.4.1.10106.3.101291.1.1.11
		gps3000p03v2SdiVidVDelay OBJECT-TYPE
			SYNTAX DelayLines1
			MAX-ACCESS read-write
			STATUS current
			DESCRIPTION
				"Allows adjusting the SDI video vertical delay"
		::= { gps3000p03v2Entry 11 }

		-- 1.3.6.1.4.1.10106.3.101291.1.1.13
		gps3000p03v2SdiVidFrDelay OBJECT-TYPE
			SYNTAX DelayFram1
			MAX-ACCESS read-write
			STATUS current
			DESCRIPTION
				"Allows adjusting the SDI video frame delay"
		::= { gps3000p03v2Entry 13 }

		-- 1.3.6.1.4.1.10106.3.101291.1.1.15
		gps3000p03v2AnaVidHDelay OBJECT-TYPE
			SYNTAX DelayPixel2
			MAX-ACCESS read-write
			STATUS current
			DESCRIPTION
				"Allows adjusting the Analog to SDI video horizontal delay"
		::= { gps3000p03v2Entry 15 }

		-- 1.3.6.1.4.1.10106.3.101291.1.1.17
		gps3000p03v2VitcInsLine OBJECT-TYPE
			SYNTAX VideoLine
			MAX-ACCESS read-write
			STATUS current
			DESCRIPTION
				"Allows adjusting the VITC insertion line"
		::= { gps3000p03v2Entry 17 }

		-- 1.3.6.1.4.1.10106.3.101291.1.1.19
		gps3000p03v2AnaVidSch OBJECT-TYPE
			SYNTAX Sch1
			MAX-ACCESS read-write
			STATUS current
			DESCRIPTION
				"Allows adjusting the Analog video SCH"
		::= { gps3000p03v2Entry 19 }

		-- 1.3.6.1.4.1.10106.3.101291.1.1.21
		gps3000p03v2HoldoverStat OBJECT-TYPE
			SYNTAX Bit0Trk1Hol
			MAX-ACCESS read-only
			STATUS current
			DESCRIPTION
				"Indicates if the module is locked to GPS or to reference or it is in holdover mode"
		::= { gps3000p03v2Entry 21 }

		-- 1.3.6.1.4.1.10106.3.101291.1.1.22
		gps3000p03v2HoldoverStatTrapEnable OBJECT-TYPE
			SYNTAX AlarmEnable
			MAX-ACCESS read-write
			STATUS current
			DESCRIPTION
				"Indicates if the module is locked to GPS or to reference or it is in holdover mode Trap Enable"
		::= { gps3000p03v2Entry 22 }

		-- 1.3.6.1.4.1.10106.3.101291.1.1.23
		gps3000p03v2RedundFail OBJECT-TYPE
			SYNTAX BitFail
			MAX-ACCESS read-only
			STATUS current
			DESCRIPTION
				"Indicates if there is any active module in the redundance system"
		::= { gps3000p03v2Entry 23 }

		-- 1.3.6.1.4.1.10106.3.101291.1.1.24
		gps3000p03v2RedundFailTrapEnable OBJECT-TYPE
			SYNTAX AlarmEnable
			MAX-ACCESS read-write
			STATUS current
			DESCRIPTION
				"Indicates if there is any active module in the redundance system Trap Enable"
		::= { gps3000p03v2Entry 24 }

		-- 1.3.6.1.4.1.10106.3.101291.1.1.25
		gps3000p03v2OutputsMuted OBJECT-TYPE
			SYNTAX BitFail
			MAX-ACCESS read-only
			STATUS current
			DESCRIPTION
				"Indicates f the module outputs are active"
		::= { gps3000p03v2Entry 25 }

		-- 1.3.6.1.4.1.10106.3.101291.1.1.26
		gps3000p03v2OutputsMutedTrapEnable OBJECT-TYPE
			SYNTAX AlarmEnable
			MAX-ACCESS read-write
			STATUS current
			DESCRIPTION
				"Indicates f the module outputs are active Trap Enable"
		::= { gps3000p03v2Entry 26 }

		-- 1.3.6.1.4.1.10106.3.101291.1.1.27
		gps3000p03v2SatRxStat OBJECT-TYPE
			SYNTAX GpsSatRxStat
			MAX-ACCESS read-only
			STATUS current
			DESCRIPTION
				"GPS receiver module satellite tracking status"
		::= { gps3000p03v2Entry 27 }

		-- 1.3.6.1.4.1.10106.3.101291.1.1.29
		gps3000p03v2AntenaStat OBJECT-TYPE
			SYNTAX GpsAntenaStat
			MAX-ACCESS read-only
			STATUS current
			DESCRIPTION
				"Antenna connection status"
		::= { gps3000p03v2Entry 29 }

		-- 1.3.6.1.4.1.10106.3.101291.1.1.30
		gps3000p03v2AntenaStatTrapEnable OBJECT-TYPE
			SYNTAX AlarmEnable
			MAX-ACCESS read-write
			STATUS current
			DESCRIPTION
				"Antenna connection status Trap Enable"
		::= { gps3000p03v2Entry 30 }

		-- 1.3.6.1.4.1.10106.3.101291.1.1.31
		gps3000p03v2SatNoFail OBJECT-TYPE
			SYNTAX BitFail
			MAX-ACCESS read-only
			STATUS current
			DESCRIPTION
				"Indicates that the number of visible satellites is low"
		::= { gps3000p03v2Entry 31 }

		-- 1.3.6.1.4.1.10106.3.101291.1.1.33
		gps3000p03v2AlmanacFail OBJECT-TYPE
			SYNTAX BitFail
			MAX-ACCESS read-only
			STATUS current
			DESCRIPTION
				"Indicates that the modules has an invalid almanac"
		::= { gps3000p03v2Entry 33 }

		-- 1.3.6.1.4.1.10106.3.101291.1.1.35
		gps3000p03v2GpsModFail OBJECT-TYPE
			SYNTAX BitFail
			MAX-ACCESS read-only
			STATUS current
			DESCRIPTION
				"Indicates that an error has been detected in the GPS receiver module"
		::= { gps3000p03v2Entry 35 }

		-- 1.3.6.1.4.1.10106.3.101291.1.1.37
		gps3000p03v2GpsTrackSats OBJECT-TYPE
			SYNTAX GpsSatellites
			MAX-ACCESS read-only
			STATUS current
			DESCRIPTION
				"Number of GPS tracking satellites"
		::= { gps3000p03v2Entry 37 }

		-- 1.3.6.1.4.1.10106.3.101291.1.1.39
		gps3000p03v2GpsVisibleSats OBJECT-TYPE
			SYNTAX GpsSatellites
			MAX-ACCESS read-only
			STATUS current
			DESCRIPTION
				"Number of GPS visible satellites"
		::= { gps3000p03v2Entry 39 }

		-- 1.3.6.1.4.1.10106.3.101291.1.1.41
		gps3000p03v2GpsSignalLevel OBJECT-TYPE
			SYNTAX LevelDbHz
			MAX-ACCESS read-only
			STATUS current
			DESCRIPTION
				"Estimated carrier to noise ratio for the best satellite in tracking"
		::= { gps3000p03v2Entry 41 }

		-- 1.3.6.1.4.1.10106.3.101291.1.1.43
		gps3000p03v2AdquisitionStat OBJECT-TYPE
			SYNTAX GpsAdqStat1
			MAX-ACCESS read-only
			STATUS current
			DESCRIPTION
				"GPS3000 module adquisition status"
		::= { gps3000p03v2Entry 43 }

		-- 1.3.6.1.4.1.10106.3.101291.1.1.45
		gps3000p03v2HoldoverTime OBJECT-TYPE
			SYNTAX GpsHoldovrTime
			MAX-ACCESS read-only
			STATUS current
			DESCRIPTION
				"Holdover time"
		::= { gps3000p03v2Entry 45 }

		-- 1.3.6.1.4.1.10106.3.101291.1.1.47
		gps3000p03v2FreqDriftEst OBJECT-TYPE
			SYNTAX GpsFrqDrftEst
			MAX-ACCESS read-only
			STATUS current
			DESCRIPTION
				"Frequency drift estimation"
		::= { gps3000p03v2Entry 47 }

		-- 1.3.6.1.4.1.10106.3.101291.1.1.49
		gps3000p03v2PhaseDriftEst OBJECT-TYPE
			SYNTAX GpsPhsDrftEst
			MAX-ACCESS read-only
			STATUS current
			DESCRIPTION
				"Phase drift estimation"
		::= { gps3000p03v2Entry 49 }

		-- 1.3.6.1.4.1.10106.3.216403
		gps3000p03v3 OBJECT IDENTIFIER ::= { albalaProducts 216403 }

		-- 1.3.6.1.4.1.10106.3.216403.1
		gps3000p03v3Table  OBJECT-TYPE
			SYNTAX SEQUENCE OF Gps3000p03v3Entry
			MAX-ACCESS not-accessible
			STATUS current
			DESCRIPTION
				"Module  GPS3000P03V3 Table"
			::= { gps3000p03v3 1 }

		-- 1.3.6.1.4.1.10106.3.216403.1.1
		gps3000p03v3Entry  OBJECT-TYPE
			SYNTAX Gps3000p03v3Entry
			MAX-ACCESS not-accessible
			STATUS current
			DESCRIPTION
				"Module GPS3000P03V3 Entry"
			INDEX { gps3000p03v3Index }
			::= { gps3000p03v3Table 1 }

			Gps3000p03v3Entry ::=
			SEQUENCE {
				gps3000p03v3Index
				ModuleIndex,
				gps3000p03v3Holdover
				Bit0Dis1Ena,
				gps3000p03v3HoldoverTrapEnable
				AlarmEnable,
				gps3000p03v3CableDelay
				DelayX2Ns,
				gps3000p03v3VideoOut
				Bit05251625,
				gps3000p03v3SdiVidHDelay
				DelayPixel1,
				gps3000p03v3SdiVidVDelay
				DelayLines1,
				gps3000p03v3SdiVidFrDelay
				DelayFram1,
				gps3000p03v3AnaVidHDelay
				DelayPixel2,
				gps3000p03v3VitcInsLine
				VideoLine,
				gps3000p03v3AnaVidSch
				Sch1,
				gps3000p03v3HoldoverStat
				Bit0Trk1Hol,
				gps3000p03v3HoldoverStatTrapEnable
				AlarmEnable,
				gps3000p03v3RedundFail
				BitFail,
				gps3000p03v3RedundFailTrapEnable
				AlarmEnable,
				gps3000p03v3OutputsMuted
				BitFail,
				gps3000p03v3OutputsMutedTrapEnable
				AlarmEnable,
				gps3000p03v3SatRxStat
				GpsSatRxStat,
				gps3000p03v3AntenaStat
				GpsAntenaStat,
				gps3000p03v3AntenaStatTrapEnable
				AlarmEnable,
				gps3000p03v3SatNoFail
				BitFail,
				gps3000p03v3AlmanacFail
				BitFail,
				gps3000p03v3GpsModFail
				BitFail,
				gps3000p03v3GpsTrackSats
				GpsSatellites,
				gps3000p03v3GpsVisibleSats
				GpsSatellites,
				gps3000p03v3GpsSignalLevel
				LevelDbHz,
				gps3000p03v3AdquisitionStat
				GpsAdqStat1,
				gps3000p03v3HoldoverTime
				GpsHoldovrTime,
				gps3000p03v3FreqDriftEst
				GpsFrqDrftEst,
				gps3000p03v3PhaseDriftEst
				GpsPhsDrftEst
			 }

		-- 1.3.6.1.4.1.10106.3.101291.1.1.1
		gps3000p03v3Index OBJECT-TYPE
			SYNTAX ModuleIndex
			MAX-ACCESS read-only
			STATUS current
			DESCRIPTION
				"Index of GPS3000P03V3 Table"
		::= { gps3000p03v3Entry 1 }

		-- 1.3.6.1.4.1.10106.3.101291.1.1.3
		gps3000p03v3Holdover OBJECT-TYPE
			SYNTAX Bit0Dis1Ena
			MAX-ACCESS read-write
			STATUS current
			DESCRIPTION
				"Allows setting the module in the holdover mode"
		::= { gps3000p03v3Entry 3 }

		-- 1.3.6.1.4.1.10106.3.101291.1.1.4
		gps3000p03v3HoldoverTrapEnable OBJECT-TYPE
			SYNTAX AlarmEnable
			MAX-ACCESS read-write
			STATUS current
			DESCRIPTION
				"Allows setting the module in the holdover mode Trap Enable"
		::= { gps3000p03v3Entry 4 }

		-- 1.3.6.1.4.1.10106.3.101291.1.1.5
		gps3000p03v3CableDelay OBJECT-TYPE
			SYNTAX DelayX2Ns
			MAX-ACCESS read-write
			STATUS current
			DESCRIPTION
				"Allows compensating the antenna cable delay"
		::= { gps3000p03v3Entry 5 }

		-- 1.3.6.1.4.1.10106.3.101291.1.1.7
		gps3000p03v3VideoOut OBJECT-TYPE
			SYNTAX Bit05251625
			MAX-ACCESS read-only
			STATUS current
			DESCRIPTION
				"Allows selecting the video output format"
		::= { gps3000p03v3Entry 7 }

		-- 1.3.6.1.4.1.10106.3.101291.1.1.9
		gps3000p03v3SdiVidHDelay OBJECT-TYPE
			SYNTAX DelayPixel1
			MAX-ACCESS read-write
			STATUS current
			DESCRIPTION
				"Allows adjusting the SDI video horizontal delay"
		::= { gps3000p03v3Entry 9 }

		-- 1.3.6.1.4.1.10106.3.101291.1.1.11
		gps3000p03v3SdiVidVDelay OBJECT-TYPE
			SYNTAX DelayLines1
			MAX-ACCESS read-write
			STATUS current
			DESCRIPTION
				"Allows adjusting the SDI video vertical delay"
		::= { gps3000p03v3Entry 11 }

		-- 1.3.6.1.4.1.10106.3.101291.1.1.13
		gps3000p03v3SdiVidFrDelay OBJECT-TYPE
			SYNTAX DelayFram1
			MAX-ACCESS read-write
			STATUS current
			DESCRIPTION
				"Allows adjusting the SDI video frame delay"
		::= { gps3000p03v3Entry 13 }

		-- 1.3.6.1.4.1.10106.3.101291.1.1.15
		gps3000p03v3AnaVidHDelay OBJECT-TYPE
			SYNTAX DelayPixel2
			MAX-ACCESS read-write
			STATUS current
			DESCRIPTION
				"Allows adjusting the Analog to SDI video horizontal delay"
		::= { gps3000p03v3Entry 15 }

		-- 1.3.6.1.4.1.10106.3.101291.1.1.17
		gps3000p03v3VitcInsLine OBJECT-TYPE
			SYNTAX VideoLine
			MAX-ACCESS read-write
			STATUS current
			DESCRIPTION
				"Allows adjusting the VITC insertion line"
		::= { gps3000p03v3Entry 17 }

		-- 1.3.6.1.4.1.10106.3.101291.1.1.19
		gps3000p03v3AnaVidSch OBJECT-TYPE
			SYNTAX Sch1
			MAX-ACCESS read-write
			STATUS current
			DESCRIPTION
				"Allows adjusting the Analog video SCH"
		::= { gps3000p03v3Entry 19 }

		-- 1.3.6.1.4.1.10106.3.101291.1.1.21
		gps3000p03v3HoldoverStat OBJECT-TYPE
			SYNTAX Bit0Trk1Hol
			MAX-ACCESS read-only
			STATUS current
			DESCRIPTION
				"Indicates if the module is locked to GPS or to reference or it is in holdover mode"
		::= { gps3000p03v3Entry 21 }

		-- 1.3.6.1.4.1.10106.3.101291.1.1.22
		gps3000p03v3HoldoverStatTrapEnable OBJECT-TYPE
			SYNTAX AlarmEnable
			MAX-ACCESS read-write
			STATUS current
			DESCRIPTION
				"Indicates if the module is locked to GPS or to reference or it is in holdover mode Trap Enable"
		::= { gps3000p03v3Entry 22 }

		-- 1.3.6.1.4.1.10106.3.101291.1.1.23
		gps3000p03v3RedundFail OBJECT-TYPE
			SYNTAX BitFail
			MAX-ACCESS read-only
			STATUS current
			DESCRIPTION
				"Indicates if there is any active module in the redundance system"
		::= { gps3000p03v3Entry 23 }

		-- 1.3.6.1.4.1.10106.3.101291.1.1.24
		gps3000p03v3RedundFailTrapEnable OBJECT-TYPE
			SYNTAX AlarmEnable
			MAX-ACCESS read-write
			STATUS current
			DESCRIPTION
				"Indicates if there is any active module in the redundance system Trap Enable"
		::= { gps3000p03v3Entry 24 }

		-- 1.3.6.1.4.1.10106.3.101291.1.1.25
		gps3000p03v3OutputsMuted OBJECT-TYPE
			SYNTAX BitFail
			MAX-ACCESS read-only
			STATUS current
			DESCRIPTION
				"Indicates f the module outputs are active"
		::= { gps3000p03v3Entry 25 }

		-- 1.3.6.1.4.1.10106.3.101291.1.1.26
		gps3000p03v3OutputsMutedTrapEnable OBJECT-TYPE
			SYNTAX AlarmEnable
			MAX-ACCESS read-write
			STATUS current
			DESCRIPTION
				"Indicates f the module outputs are active Trap Enable"
		::= { gps3000p03v3Entry 26 }

		-- 1.3.6.1.4.1.10106.3.101291.1.1.27
		gps3000p03v3SatRxStat OBJECT-TYPE
			SYNTAX GpsSatRxStat
			MAX-ACCESS read-only
			STATUS current
			DESCRIPTION
				"GPS receiver module satellite tracking status"
		::= { gps3000p03v3Entry 27 }

		-- 1.3.6.1.4.1.10106.3.101291.1.1.29
		gps3000p03v3AntenaStat OBJECT-TYPE
			SYNTAX GpsAntenaStat
			MAX-ACCESS read-only
			STATUS current
			DESCRIPTION
				"Antenna connection status"
		::= { gps3000p03v3Entry 29 }

		-- 1.3.6.1.4.1.10106.3.101291.1.1.30
		gps3000p03v3AntenaStatTrapEnable OBJECT-TYPE
			SYNTAX AlarmEnable
			MAX-ACCESS read-write
			STATUS current
			DESCRIPTION
				"Antenna connection status Trap Enable"
		::= { gps3000p03v3Entry 30 }

		-- 1.3.6.1.4.1.10106.3.101291.1.1.31
		gps3000p03v3SatNoFail OBJECT-TYPE
			SYNTAX BitFail
			MAX-ACCESS read-only
			STATUS current
			DESCRIPTION
				"Indicates that the number of visible satellites is low"
		::= { gps3000p03v3Entry 31 }

		-- 1.3.6.1.4.1.10106.3.101291.1.1.33
		gps3000p03v3AlmanacFail OBJECT-TYPE
			SYNTAX BitFail
			MAX-ACCESS read-only
			STATUS current
			DESCRIPTION
				"Indicates that the modules has an invalid almanac"
		::= { gps3000p03v3Entry 33 }

		-- 1.3.6.1.4.1.10106.3.101291.1.1.35
		gps3000p03v3GpsModFail OBJECT-TYPE
			SYNTAX BitFail
			MAX-ACCESS read-only
			STATUS current
			DESCRIPTION
				"Indicates that an error has been detected in the GPS receiver module"
		::= { gps3000p03v3Entry 35 }

		-- 1.3.6.1.4.1.10106.3.101291.1.1.37
		gps3000p03v3GpsTrackSats OBJECT-TYPE
			SYNTAX GpsSatellites
			MAX-ACCESS read-only
			STATUS current
			DESCRIPTION
				"Number of GPS tracking satellites"
		::= { gps3000p03v3Entry 37 }

		-- 1.3.6.1.4.1.10106.3.101291.1.1.39
		gps3000p03v3GpsVisibleSats OBJECT-TYPE
			SYNTAX GpsSatellites
			MAX-ACCESS read-only
			STATUS current
			DESCRIPTION
				"Number of GPS visible satellites"
		::= { gps3000p03v3Entry 39 }

		-- 1.3.6.1.4.1.10106.3.101291.1.1.41
		gps3000p03v3GpsSignalLevel OBJECT-TYPE
			SYNTAX LevelDbHz
			MAX-ACCESS read-only
			STATUS current
			DESCRIPTION
				"Estimated carrier to noise ratio for the best satellite in tracking"
		::= { gps3000p03v3Entry 41 }

		-- 1.3.6.1.4.1.10106.3.101291.1.1.43
		gps3000p03v3AdquisitionStat OBJECT-TYPE
			SYNTAX GpsAdqStat1
			MAX-ACCESS read-only
			STATUS current
			DESCRIPTION
				"GPS3000 module adquisition status"
		::= { gps3000p03v3Entry 43 }

		-- 1.3.6.1.4.1.10106.3.101291.1.1.45
		gps3000p03v3HoldoverTime OBJECT-TYPE
			SYNTAX GpsHoldovrTime
			MAX-ACCESS read-only
			STATUS current
			DESCRIPTION
				"Holdover time"
		::= { gps3000p03v3Entry 45 }

		-- 1.3.6.1.4.1.10106.3.101291.1.1.47
		gps3000p03v3FreqDriftEst OBJECT-TYPE
			SYNTAX GpsFrqDrftEst
			MAX-ACCESS read-only
			STATUS current
			DESCRIPTION
				"Frequency drift estimation"
		::= { gps3000p03v3Entry 47 }

		-- 1.3.6.1.4.1.10106.3.101291.1.1.49
		gps3000p03v3PhaseDriftEst OBJECT-TYPE
			SYNTAX GpsPhsDrftEst
			MAX-ACCESS read-only
			STATUS current
			DESCRIPTION
				"Phase drift estimation"
		::= { gps3000p03v3Entry 49 }

		-- 1.3.6.1.4.1.10106.3.216404
		gps3000p03v4 OBJECT IDENTIFIER ::= { albalaProducts 216404 }

		-- 1.3.6.1.4.1.10106.3.216404.1
		gps3000p03v4Table  OBJECT-TYPE
			SYNTAX SEQUENCE OF Gps3000p03v4Entry
			MAX-ACCESS not-accessible
			STATUS current
			DESCRIPTION
				"Module  GPS3000P03V4 Table"
			::= { gps3000p03v4 1 }

		-- 1.3.6.1.4.1.10106.3.216404.1.1
		gps3000p03v4Entry  OBJECT-TYPE
			SYNTAX Gps3000p03v4Entry
			MAX-ACCESS not-accessible
			STATUS current
			DESCRIPTION
				"Module GPS3000P03V4 Entry"
			INDEX { gps3000p03v4Index }
			::= { gps3000p03v4Table 1 }

			Gps3000p03v4Entry ::=
			SEQUENCE {
				gps3000p03v4Index
				ModuleIndex,
				gps3000p03v4Holdover
				Bit0Dis1Ena,
				gps3000p03v4HoldoverTrapEnable
				AlarmEnable,
				gps3000p03v4CableDelay
				DelayX2Ns,
				gps3000p03v4VideoOut
				Bit05251625,
				gps3000p03v4SdiVidHDelay
				DelayPixel1,
				gps3000p03v4SdiVidVDelay
				DelayLines1,
				gps3000p03v4SdiVidFrDelay
				DelayFram1,
				gps3000p03v4AnaVidHDelay
				DelayPixel2,
				gps3000p03v4VitcInsLine
				VideoLine,
				gps3000p03v4AnaVidSch
				Sch1,
				gps3000p03v4HoldoverStat
				Bit0Trk1Hol,
				gps3000p03v4HoldoverStatTrapEnable
				AlarmEnable,
				gps3000p03v4RedundFail
				BitFail,
				gps3000p03v4RedundFailTrapEnable
				AlarmEnable,
				gps3000p03v4OutputsMuted
				BitFail,
				gps3000p03v4OutputsMutedTrapEnable
				AlarmEnable,
				gps3000p03v4SatRxStat
				GpsSatRxStat,
				gps3000p03v4AntenaStat
				GpsAntenaStat,
				gps3000p03v4AntenaStatTrapEnable
				AlarmEnable,
				gps3000p03v4SatNoFail
				BitFail,
				gps3000p03v4AlmanacFail
				BitFail,
				gps3000p03v4GpsModFail
				BitFail,
				gps3000p03v4GpsTrackSats
				GpsSatellites,
				gps3000p03v4GpsVisibleSats
				GpsSatellites,
				gps3000p03v4GpsSignalLevel
				LevelDbHz,
				gps3000p03v4AdquisitionStat
				GpsAdqStat1,
				gps3000p03v4HoldoverTime
				GpsHoldovrTime,
				gps3000p03v4FreqDriftEst
				GpsFrqDrftEst,
				gps3000p03v4PhaseDriftEst
				GpsPhsDrftEst
			 }

		-- 1.3.6.1.4.1.10106.3.101291.1.1.1
		gps3000p03v4Index OBJECT-TYPE
			SYNTAX ModuleIndex
			MAX-ACCESS read-only
			STATUS current
			DESCRIPTION
				"Index of GPS3000P03V4 Table"
		::= { gps3000p03v4Entry 1 }

		-- 1.3.6.1.4.1.10106.3.101291.1.1.3
		gps3000p03v4Holdover OBJECT-TYPE
			SYNTAX Bit0Dis1Ena
			MAX-ACCESS read-write
			STATUS current
			DESCRIPTION
				"Allows setting the module in the holdover mode"
		::= { gps3000p03v4Entry 3 }

		-- 1.3.6.1.4.1.10106.3.101291.1.1.4
		gps3000p03v4HoldoverTrapEnable OBJECT-TYPE
			SYNTAX AlarmEnable
			MAX-ACCESS read-write
			STATUS current
			DESCRIPTION
				"Allows setting the module in the holdover mode Trap Enable"
		::= { gps3000p03v4Entry 4 }

		-- 1.3.6.1.4.1.10106.3.101291.1.1.5
		gps3000p03v4CableDelay OBJECT-TYPE
			SYNTAX DelayX2Ns
			MAX-ACCESS read-write
			STATUS current
			DESCRIPTION
				"Allows compensating the antenna cable delay"
		::= { gps3000p03v4Entry 5 }

		-- 1.3.6.1.4.1.10106.3.101291.1.1.7
		gps3000p03v4VideoOut OBJECT-TYPE
			SYNTAX Bit05251625
			MAX-ACCESS read-only
			STATUS current
			DESCRIPTION
				"Allows selecting the video output format"
		::= { gps3000p03v4Entry 7 }

		-- 1.3.6.1.4.1.10106.3.101291.1.1.9
		gps3000p03v4SdiVidHDelay OBJECT-TYPE
			SYNTAX DelayPixel1
			MAX-ACCESS read-write
			STATUS current
			DESCRIPTION
				"Allows adjusting the SDI video horizontal delay"
		::= { gps3000p03v4Entry 9 }

		-- 1.3.6.1.4.1.10106.3.101291.1.1.11
		gps3000p03v4SdiVidVDelay OBJECT-TYPE
			SYNTAX DelayLines1
			MAX-ACCESS read-write
			STATUS current
			DESCRIPTION
				"Allows adjusting the SDI video vertical delay"
		::= { gps3000p03v4Entry 11 }

		-- 1.3.6.1.4.1.10106.3.101291.1.1.13
		gps3000p03v4SdiVidFrDelay OBJECT-TYPE
			SYNTAX DelayFram1
			MAX-ACCESS read-write
			STATUS current
			DESCRIPTION
				"Allows adjusting the SDI video frame delay"
		::= { gps3000p03v4Entry 13 }

		-- 1.3.6.1.4.1.10106.3.101291.1.1.15
		gps3000p03v4AnaVidHDelay OBJECT-TYPE
			SYNTAX DelayPixel2
			MAX-ACCESS read-write
			STATUS current
			DESCRIPTION
				"Allows adjusting the Analog to SDI video horizontal delay"
		::= { gps3000p03v4Entry 15 }

		-- 1.3.6.1.4.1.10106.3.101291.1.1.17
		gps3000p03v4VitcInsLine OBJECT-TYPE
			SYNTAX VideoLine
			MAX-ACCESS read-write
			STATUS current
			DESCRIPTION
				"Allows adjusting the VITC insertion line"
		::= { gps3000p03v4Entry 17 }

		-- 1.3.6.1.4.1.10106.3.101291.1.1.19
		gps3000p03v4AnaVidSch OBJECT-TYPE
			SYNTAX Sch1
			MAX-ACCESS read-write
			STATUS current
			DESCRIPTION
				"Allows adjusting the Analog video SCH"
		::= { gps3000p03v4Entry 19 }

		-- 1.3.6.1.4.1.10106.3.101291.1.1.21
		gps3000p03v4HoldoverStat OBJECT-TYPE
			SYNTAX Bit0Trk1Hol
			MAX-ACCESS read-only
			STATUS current
			DESCRIPTION
				"Indicates if the module is locked to GPS or to reference or it is in holdover mode"
		::= { gps3000p03v4Entry 21 }

		-- 1.3.6.1.4.1.10106.3.101291.1.1.22
		gps3000p03v4HoldoverStatTrapEnable OBJECT-TYPE
			SYNTAX AlarmEnable
			MAX-ACCESS read-write
			STATUS current
			DESCRIPTION
				"Indicates if the module is locked to GPS or to reference or it is in holdover mode Trap Enable"
		::= { gps3000p03v4Entry 22 }

		-- 1.3.6.1.4.1.10106.3.101291.1.1.23
		gps3000p03v4RedundFail OBJECT-TYPE
			SYNTAX BitFail
			MAX-ACCESS read-only
			STATUS current
			DESCRIPTION
				"Indicates if there is any active module in the redundance system"
		::= { gps3000p03v4Entry 23 }

		-- 1.3.6.1.4.1.10106.3.101291.1.1.24
		gps3000p03v4RedundFailTrapEnable OBJECT-TYPE
			SYNTAX AlarmEnable
			MAX-ACCESS read-write
			STATUS current
			DESCRIPTION
				"Indicates if there is any active module in the redundance system Trap Enable"
		::= { gps3000p03v4Entry 24 }

		-- 1.3.6.1.4.1.10106.3.101291.1.1.25
		gps3000p03v4OutputsMuted OBJECT-TYPE
			SYNTAX BitFail
			MAX-ACCESS read-only
			STATUS current
			DESCRIPTION
				"Indicates f the module outputs are active"
		::= { gps3000p03v4Entry 25 }

		-- 1.3.6.1.4.1.10106.3.101291.1.1.26
		gps3000p03v4OutputsMutedTrapEnable OBJECT-TYPE
			SYNTAX AlarmEnable
			MAX-ACCESS read-write
			STATUS current
			DESCRIPTION
				"Indicates f the module outputs are active Trap Enable"
		::= { gps3000p03v4Entry 26 }

		-- 1.3.6.1.4.1.10106.3.101291.1.1.27
		gps3000p03v4SatRxStat OBJECT-TYPE
			SYNTAX GpsSatRxStat
			MAX-ACCESS read-only
			STATUS current
			DESCRIPTION
				"GPS receiver module satellite tracking status"
		::= { gps3000p03v4Entry 27 }

		-- 1.3.6.1.4.1.10106.3.101291.1.1.29
		gps3000p03v4AntenaStat OBJECT-TYPE
			SYNTAX GpsAntenaStat
			MAX-ACCESS read-only
			STATUS current
			DESCRIPTION
				"Antenna connection status"
		::= { gps3000p03v4Entry 29 }

		-- 1.3.6.1.4.1.10106.3.101291.1.1.30
		gps3000p03v4AntenaStatTrapEnable OBJECT-TYPE
			SYNTAX AlarmEnable
			MAX-ACCESS read-write
			STATUS current
			DESCRIPTION
				"Antenna connection status Trap Enable"
		::= { gps3000p03v4Entry 30 }

		-- 1.3.6.1.4.1.10106.3.101291.1.1.31
		gps3000p03v4SatNoFail OBJECT-TYPE
			SYNTAX BitFail
			MAX-ACCESS read-only
			STATUS current
			DESCRIPTION
				"Indicates that the number of visible satellites is low"
		::= { gps3000p03v4Entry 31 }

		-- 1.3.6.1.4.1.10106.3.101291.1.1.33
		gps3000p03v4AlmanacFail OBJECT-TYPE
			SYNTAX BitFail
			MAX-ACCESS read-only
			STATUS current
			DESCRIPTION
				"Indicates that the modules has an invalid almanac"
		::= { gps3000p03v4Entry 33 }

		-- 1.3.6.1.4.1.10106.3.101291.1.1.35
		gps3000p03v4GpsModFail OBJECT-TYPE
			SYNTAX BitFail
			MAX-ACCESS read-only
			STATUS current
			DESCRIPTION
				"Indicates that an error has been detected in the GPS receiver module"
		::= { gps3000p03v4Entry 35 }

		-- 1.3.6.1.4.1.10106.3.101291.1.1.37
		gps3000p03v4GpsTrackSats OBJECT-TYPE
			SYNTAX GpsSatellites
			MAX-ACCESS read-only
			STATUS current
			DESCRIPTION
				"Number of GPS tracking satellites"
		::= { gps3000p03v4Entry 37 }

		-- 1.3.6.1.4.1.10106.3.101291.1.1.39
		gps3000p03v4GpsVisibleSats OBJECT-TYPE
			SYNTAX GpsSatellites
			MAX-ACCESS read-only
			STATUS current
			DESCRIPTION
				"Number of GPS visible satellites"
		::= { gps3000p03v4Entry 39 }

		-- 1.3.6.1.4.1.10106.3.101291.1.1.41
		gps3000p03v4GpsSignalLevel OBJECT-TYPE
			SYNTAX LevelDbHz
			MAX-ACCESS read-only
			STATUS current
			DESCRIPTION
				"Estimated carrier to noise ratio for the best satellite in tracking"
		::= { gps3000p03v4Entry 41 }

		-- 1.3.6.1.4.1.10106.3.101291.1.1.43
		gps3000p03v4AdquisitionStat OBJECT-TYPE
			SYNTAX GpsAdqStat1
			MAX-ACCESS read-only
			STATUS current
			DESCRIPTION
				"GPS3000 module adquisition status"
		::= { gps3000p03v4Entry 43 }

		-- 1.3.6.1.4.1.10106.3.101291.1.1.45
		gps3000p03v4HoldoverTime OBJECT-TYPE
			SYNTAX GpsHoldovrTime
			MAX-ACCESS read-only
			STATUS current
			DESCRIPTION
				"Holdover time"
		::= { gps3000p03v4Entry 45 }

		-- 1.3.6.1.4.1.10106.3.101291.1.1.47
		gps3000p03v4FreqDriftEst OBJECT-TYPE
			SYNTAX GpsFrqDrftEst
			MAX-ACCESS read-only
			STATUS current
			DESCRIPTION
				"Frequency drift estimation"
		::= { gps3000p03v4Entry 47 }

		-- 1.3.6.1.4.1.10106.3.101291.1.1.49
		gps3000p03v4PhaseDriftEst OBJECT-TYPE
			SYNTAX GpsPhsDrftEst
			MAX-ACCESS read-only
			STATUS current
			DESCRIPTION
				"Phase drift estimation"
		::= { gps3000p03v4Entry 49 }

		-- 1.3.6.1.4.1.10106.3.224701
		frs3004c02v1 OBJECT IDENTIFIER ::= { albalaProducts 224701 }

		-- 1.3.6.1.4.1.10106.3.224701.1
		frs3004c02v1Table  OBJECT-TYPE
			SYNTAX SEQUENCE OF Frs3004c02v1Entry
			MAX-ACCESS not-accessible
			STATUS current
			DESCRIPTION
				"Module  FRS3004C02V1 Table"
			::= { frs3004c02v1 1 }

		-- 1.3.6.1.4.1.10106.3.224701.1.1
		frs3004c02v1Entry  OBJECT-TYPE
			SYNTAX Frs3004c02v1Entry
			MAX-ACCESS not-accessible
			STATUS current
			DESCRIPTION
				"Module FRS3004C02V1 Entry"
			INDEX { frs3004c02v1Index }
			::= { frs3004c02v1Table 1 }

			Frs3004c02v1Entry ::=
			SEQUENCE {
				frs3004c02v1Index
				ModuleIndex,
				frs3004c02v1RefSource
				Bit0Ana1Dig,
				frs3004c02v1FailMode
				Bit0Fre1Blk,
				frs3004c02v1SynchroMode
				Bit0Fra1Lin,
				frs3004c02v1VbiMode
				Bit0Pas1Bnk,
				frs3004c02v1HDelay1
				DelayPixel1,
				frs3004c02v1VDelay1
				DelayLines1,
				frs3004c02v1LumaGain1
				GainLin1,
				frs3004c02v1ChromaGain1
				GainLin1,
				frs3004c02v1BlackOffset1
				BlackOffset1,
				frs3004c02v1HDelay2
				DelayPixel1,
				frs3004c02v1VDelay2
				DelayLines1,
				frs3004c02v1LumaGain2
				GainLin1,
				frs3004c02v1ChromaGain2
				GainLin1,
				frs3004c02v1BlackOffset2
				BlackOffset1,
				frs3004c02v1HDelay3
				DelayPixel1,
				frs3004c02v1VDelay3
				DelayLines1,
				frs3004c02v1LumaGain3
				GainLin1,
				frs3004c02v1ChromaGain3
				GainLin1,
				frs3004c02v1BlackOffset3
				BlackOffset1,
				frs3004c02v1HDelay4
				DelayPixel1,
				frs3004c02v1VDelay4
				DelayLines1,
				frs3004c02v1LumaGain4
				GainLin1,
				frs3004c02v1ChromaGain4
				GainLin1,
				frs3004c02v1BlackOffset4
				BlackOffset1,
				frs3004c02v1NoRef
				BitFail,
				frs3004c02v1NoRefTrapEnable
				AlarmEnable,
				frs3004c02v1RefUnlock
				BitFail,
				frs3004c02v1RefUnlockTrapEnable
				AlarmEnable,
				frs3004c02v1RefEdhError
				BitFail,
				frs3004c02v1RefLines
				Bit05251625,
				frs3004c02v1NoSig1
				BitFail,
				frs3004c02v1NoSig1TrapEnable
				AlarmEnable,
				frs3004c02v1NoSig2
				BitFail,
				frs3004c02v1NoSig2TrapEnable
				AlarmEnable,
				frs3004c02v1NoSig3
				BitFail,
				frs3004c02v1NoSig3TrapEnable
				AlarmEnable,
				frs3004c02v1NoSig4
				BitFail,
				frs3004c02v1NoSig4TrapEnable
				AlarmEnable,
				frs3004c02v1EdhError1
				BitFail,
				frs3004c02v1EdhError2
				BitFail,
				frs3004c02v1EdhError3
				BitFail,
				frs3004c02v1EdhError4
				BitFail,
				frs3004c02v1Sig1Delay
				DelayX20Us,
				frs3004c02v1Sig2Delay
				DelayX20Us,
				frs3004c02v1Sig3Delay
				DelayX20Us,
				frs3004c02v1Sig4Delay
				DelayX20Us,
				frs3004c02v1SerialNo
				SerialNo
			 }

		-- 1.3.6.1.4.1.10106.3.101291.1.1.1
		frs3004c02v1Index OBJECT-TYPE
			SYNTAX ModuleIndex
			MAX-ACCESS read-only
			STATUS current
			DESCRIPTION
				"Index of FRS3004C02V1 Table"
		::= { frs3004c02v1Entry 1 }

		-- 1.3.6.1.4.1.10106.3.101291.1.1.3
		frs3004c02v1RefSource OBJECT-TYPE
			SYNTAX Bit0Ana1Dig
			MAX-ACCESS read-write
			STATUS current
			DESCRIPTION
				"Allows selecting the reference signal"
		::= { frs3004c02v1Entry 3 }

		-- 1.3.6.1.4.1.10106.3.101291.1.1.5
		frs3004c02v1FailMode OBJECT-TYPE
			SYNTAX Bit0Fre1Blk
			MAX-ACCESS read-write
			STATUS current
			DESCRIPTION
				"Allows selecting the output video signal if the input fails"
		::= { frs3004c02v1Entry 5 }

		-- 1.3.6.1.4.1.10106.3.101291.1.1.7
		frs3004c02v1SynchroMode OBJECT-TYPE
			SYNTAX Bit0Fra1Lin
			MAX-ACCESS read-write
			STATUS current
			DESCRIPTION
				"Allows selecting the synchronizing mode"
		::= { frs3004c02v1Entry 7 }

		-- 1.3.6.1.4.1.10106.3.101291.1.1.9
		frs3004c02v1VbiMode OBJECT-TYPE
			SYNTAX Bit0Pas1Bnk
			MAX-ACCESS read-write
			STATUS current
			DESCRIPTION
				"Allows selecting if the VBI is blanked"
		::= { frs3004c02v1Entry 9 }

		-- 1.3.6.1.4.1.10106.3.101291.1.1.11
		frs3004c02v1HDelay1 OBJECT-TYPE
			SYNTAX DelayPixel1
			MAX-ACCESS read-write
			STATUS current
			DESCRIPTION
				"Allows adjusting the video horizontal delay"
		::= { frs3004c02v1Entry 11 }

		-- 1.3.6.1.4.1.10106.3.101291.1.1.13
		frs3004c02v1VDelay1 OBJECT-TYPE
			SYNTAX DelayLines1
			MAX-ACCESS read-write
			STATUS current
			DESCRIPTION
				"Allows adjusting the video vertical delay"
		::= { frs3004c02v1Entry 13 }

		-- 1.3.6.1.4.1.10106.3.101291.1.1.15
		frs3004c02v1LumaGain1 OBJECT-TYPE
			SYNTAX GainLin1
			MAX-ACCESS read-write
			STATUS current
			DESCRIPTION
				"Allows adjusting the luma gain"
		::= { frs3004c02v1Entry 15 }

		-- 1.3.6.1.4.1.10106.3.101291.1.1.17
		frs3004c02v1ChromaGain1 OBJECT-TYPE
			SYNTAX GainLin1
			MAX-ACCESS read-write
			STATUS current
			DESCRIPTION
				"Allows adjusting the chorma gain"
		::= { frs3004c02v1Entry 17 }

		-- 1.3.6.1.4.1.10106.3.101291.1.1.19
		frs3004c02v1BlackOffset1 OBJECT-TYPE
			SYNTAX BlackOffset1
			MAX-ACCESS read-write
			STATUS current
			DESCRIPTION
				"Allows adjusting the black offset"
		::= { frs3004c02v1Entry 19 }

		-- 1.3.6.1.4.1.10106.3.101291.1.1.21
		frs3004c02v1HDelay2 OBJECT-TYPE
			SYNTAX DelayPixel1
			MAX-ACCESS read-write
			STATUS current
			DESCRIPTION
				"Allows adjusting the video horizontal delay"
		::= { frs3004c02v1Entry 21 }

		-- 1.3.6.1.4.1.10106.3.101291.1.1.23
		frs3004c02v1VDelay2 OBJECT-TYPE
			SYNTAX DelayLines1
			MAX-ACCESS read-write
			STATUS current
			DESCRIPTION
				"Allows adjusting the video vertical delay"
		::= { frs3004c02v1Entry 23 }

		-- 1.3.6.1.4.1.10106.3.101291.1.1.25
		frs3004c02v1LumaGain2 OBJECT-TYPE
			SYNTAX GainLin1
			MAX-ACCESS read-write
			STATUS current
			DESCRIPTION
				"Allows adjusting the luma gain"
		::= { frs3004c02v1Entry 25 }

		-- 1.3.6.1.4.1.10106.3.101291.1.1.27
		frs3004c02v1ChromaGain2 OBJECT-TYPE
			SYNTAX GainLin1
			MAX-ACCESS read-write
			STATUS current
			DESCRIPTION
				"Allows adjusting the chorma gain"
		::= { frs3004c02v1Entry 27 }

		-- 1.3.6.1.4.1.10106.3.101291.1.1.29
		frs3004c02v1BlackOffset2 OBJECT-TYPE
			SYNTAX BlackOffset1
			MAX-ACCESS read-write
			STATUS current
			DESCRIPTION
				"Allows adjusting the black offset"
		::= { frs3004c02v1Entry 29 }

		-- 1.3.6.1.4.1.10106.3.101291.1.1.31
		frs3004c02v1HDelay3 OBJECT-TYPE
			SYNTAX DelayPixel1
			MAX-ACCESS read-write
			STATUS current
			DESCRIPTION
				"Allows adjusting the video horizontal delay"
		::= { frs3004c02v1Entry 31 }

		-- 1.3.6.1.4.1.10106.3.101291.1.1.33
		frs3004c02v1VDelay3 OBJECT-TYPE
			SYNTAX DelayLines1
			MAX-ACCESS read-write
			STATUS current
			DESCRIPTION
				"Allows adjusting the video vertical delay"
		::= { frs3004c02v1Entry 33 }

		-- 1.3.6.1.4.1.10106.3.101291.1.1.35
		frs3004c02v1LumaGain3 OBJECT-TYPE
			SYNTAX GainLin1
			MAX-ACCESS read-write
			STATUS current
			DESCRIPTION
				"Allows adjusting the luma gain"
		::= { frs3004c02v1Entry 35 }

		-- 1.3.6.1.4.1.10106.3.101291.1.1.37
		frs3004c02v1ChromaGain3 OBJECT-TYPE
			SYNTAX GainLin1
			MAX-ACCESS read-write
			STATUS current
			DESCRIPTION
				"Allows adjusting the chorma gain"
		::= { frs3004c02v1Entry 37 }

		-- 1.3.6.1.4.1.10106.3.101291.1.1.39
		frs3004c02v1BlackOffset3 OBJECT-TYPE
			SYNTAX BlackOffset1
			MAX-ACCESS read-write
			STATUS current
			DESCRIPTION
				"Allows adjusting the black offset"
		::= { frs3004c02v1Entry 39 }

		-- 1.3.6.1.4.1.10106.3.101291.1.1.41
		frs3004c02v1HDelay4 OBJECT-TYPE
			SYNTAX DelayPixel1
			MAX-ACCESS read-write
			STATUS current
			DESCRIPTION
				"Allows adjusting the video horizontal delay"
		::= { frs3004c02v1Entry 41 }

		-- 1.3.6.1.4.1.10106.3.101291.1.1.43
		frs3004c02v1VDelay4 OBJECT-TYPE
			SYNTAX DelayLines1
			MAX-ACCESS read-write
			STATUS current
			DESCRIPTION
				"Allows adjusting the video vertical delay"
		::= { frs3004c02v1Entry 43 }

		-- 1.3.6.1.4.1.10106.3.101291.1.1.45
		frs3004c02v1LumaGain4 OBJECT-TYPE
			SYNTAX GainLin1
			MAX-ACCESS read-write
			STATUS current
			DESCRIPTION
				"Allows adjusting the luma gain"
		::= { frs3004c02v1Entry 45 }

		-- 1.3.6.1.4.1.10106.3.101291.1.1.47
		frs3004c02v1ChromaGain4 OBJECT-TYPE
			SYNTAX GainLin1
			MAX-ACCESS read-write
			STATUS current
			DESCRIPTION
				"Allows adjusting the chorma gain"
		::= { frs3004c02v1Entry 47 }

		-- 1.3.6.1.4.1.10106.3.101291.1.1.49
		frs3004c02v1BlackOffset4 OBJECT-TYPE
			SYNTAX BlackOffset1
			MAX-ACCESS read-write
			STATUS current
			DESCRIPTION
				"Allows adjusting the black offset"
		::= { frs3004c02v1Entry 49 }

		-- 1.3.6.1.4.1.10106.3.101291.1.1.51
		frs3004c02v1NoRef OBJECT-TYPE
			SYNTAX BitFail
			MAX-ACCESS read-only
			STATUS current
			DESCRIPTION
				"Indicates reference signal fail"
		::= { frs3004c02v1Entry 51 }

		-- 1.3.6.1.4.1.10106.3.101291.1.1.52
		frs3004c02v1NoRefTrapEnable OBJECT-TYPE
			SYNTAX AlarmEnable
			MAX-ACCESS read-write
			STATUS current
			DESCRIPTION
				"Indicates reference signal fail Trap Enable"
		::= { frs3004c02v1Entry 52 }

		-- 1.3.6.1.4.1.10106.3.101291.1.1.53
		frs3004c02v1RefUnlock OBJECT-TYPE
			SYNTAX BitFail
			MAX-ACCESS read-only
			STATUS current
			DESCRIPTION
				"Indicates reference signal unlock fail"
		::= { frs3004c02v1Entry 53 }

		-- 1.3.6.1.4.1.10106.3.101291.1.1.54
		frs3004c02v1RefUnlockTrapEnable OBJECT-TYPE
			SYNTAX AlarmEnable
			MAX-ACCESS read-write
			STATUS current
			DESCRIPTION
				"Indicates reference signal unlock fail Trap Enable"
		::= { frs3004c02v1Entry 54 }

		-- 1.3.6.1.4.1.10106.3.101291.1.1.55
		frs3004c02v1RefEdhError OBJECT-TYPE
			SYNTAX BitFail
			MAX-ACCESS read-only
			STATUS current
			DESCRIPTION
				"Indicates reference if there are EDH errors in the reference signal"
		::= { frs3004c02v1Entry 55 }

		-- 1.3.6.1.4.1.10106.3.101291.1.1.57
		frs3004c02v1RefLines OBJECT-TYPE
			SYNTAX Bit05251625
			MAX-ACCESS read-only
			STATUS current
			DESCRIPTION
				"Indicates the reference signal format"
		::= { frs3004c02v1Entry 57 }

		-- 1.3.6.1.4.1.10106.3.101291.1.1.59
		frs3004c02v1NoSig1 OBJECT-TYPE
			SYNTAX BitFail
			MAX-ACCESS read-only
			STATUS current
			DESCRIPTION
				"Indicates SDI signal fail"
		::= { frs3004c02v1Entry 59 }

		-- 1.3.6.1.4.1.10106.3.101291.1.1.60
		frs3004c02v1NoSig1TrapEnable OBJECT-TYPE
			SYNTAX AlarmEnable
			MAX-ACCESS read-write
			STATUS current
			DESCRIPTION
				"Indicates SDI signal fail Trap Enable"
		::= { frs3004c02v1Entry 60 }

		-- 1.3.6.1.4.1.10106.3.101291.1.1.61
		frs3004c02v1NoSig2 OBJECT-TYPE
			SYNTAX BitFail
			MAX-ACCESS read-only
			STATUS current
			DESCRIPTION
				"Indicates SDI signal fail"
		::= { frs3004c02v1Entry 61 }

		-- 1.3.6.1.4.1.10106.3.101291.1.1.62
		frs3004c02v1NoSig2TrapEnable OBJECT-TYPE
			SYNTAX AlarmEnable
			MAX-ACCESS read-write
			STATUS current
			DESCRIPTION
				"Indicates SDI signal fail Trap Enable"
		::= { frs3004c02v1Entry 62 }

		-- 1.3.6.1.4.1.10106.3.101291.1.1.63
		frs3004c02v1NoSig3 OBJECT-TYPE
			SYNTAX BitFail
			MAX-ACCESS read-only
			STATUS current
			DESCRIPTION
				"Indicates SDI signal fail"
		::= { frs3004c02v1Entry 63 }

		-- 1.3.6.1.4.1.10106.3.101291.1.1.64
		frs3004c02v1NoSig3TrapEnable OBJECT-TYPE
			SYNTAX AlarmEnable
			MAX-ACCESS read-write
			STATUS current
			DESCRIPTION
				"Indicates SDI signal fail Trap Enable"
		::= { frs3004c02v1Entry 64 }

		-- 1.3.6.1.4.1.10106.3.101291.1.1.65
		frs3004c02v1NoSig4 OBJECT-TYPE
			SYNTAX BitFail
			MAX-ACCESS read-only
			STATUS current
			DESCRIPTION
				"Indicates SDI signal fail"
		::= { frs3004c02v1Entry 65 }

		-- 1.3.6.1.4.1.10106.3.101291.1.1.66
		frs3004c02v1NoSig4TrapEnable OBJECT-TYPE
			SYNTAX AlarmEnable
			MAX-ACCESS read-write
			STATUS current
			DESCRIPTION
				"Indicates SDI signal fail Trap Enable"
		::= { frs3004c02v1Entry 66 }

		-- 1.3.6.1.4.1.10106.3.101291.1.1.67
		frs3004c02v1EdhError1 OBJECT-TYPE
			SYNTAX BitFail
			MAX-ACCESS read-only
			STATUS current
			DESCRIPTION
				"Indicates error in SDI signal"
		::= { frs3004c02v1Entry 67 }

		-- 1.3.6.1.4.1.10106.3.101291.1.1.69
		frs3004c02v1EdhError2 OBJECT-TYPE
			SYNTAX BitFail
			MAX-ACCESS read-only
			STATUS current
			DESCRIPTION
				"Indicates error in SDI signal"
		::= { frs3004c02v1Entry 69 }

		-- 1.3.6.1.4.1.10106.3.101291.1.1.71
		frs3004c02v1EdhError3 OBJECT-TYPE
			SYNTAX BitFail
			MAX-ACCESS read-only
			STATUS current
			DESCRIPTION
				"Indicates error in SDI signal"
		::= { frs3004c02v1Entry 71 }

		-- 1.3.6.1.4.1.10106.3.101291.1.1.73
		frs3004c02v1EdhError4 OBJECT-TYPE
			SYNTAX BitFail
			MAX-ACCESS read-only
			STATUS current
			DESCRIPTION
				"Indicates error in SDI signal"
		::= { frs3004c02v1Entry 73 }

		-- 1.3.6.1.4.1.10106.3.101291.1.1.75
		frs3004c02v1Sig1Delay OBJECT-TYPE
			SYNTAX DelayX20Us
			MAX-ACCESS read-only
			STATUS current
			DESCRIPTION
				"Indicates the input to output delay"
		::= { frs3004c02v1Entry 75 }

		-- 1.3.6.1.4.1.10106.3.101291.1.1.77
		frs3004c02v1Sig2Delay OBJECT-TYPE
			SYNTAX DelayX20Us
			MAX-ACCESS read-only
			STATUS current
			DESCRIPTION
				"Indicates the input to output delay"
		::= { frs3004c02v1Entry 77 }

		-- 1.3.6.1.4.1.10106.3.101291.1.1.79
		frs3004c02v1Sig3Delay OBJECT-TYPE
			SYNTAX DelayX20Us
			MAX-ACCESS read-only
			STATUS current
			DESCRIPTION
				"Indicates the input to output delay"
		::= { frs3004c02v1Entry 79 }

		-- 1.3.6.1.4.1.10106.3.101291.1.1.81
		frs3004c02v1Sig4Delay OBJECT-TYPE
			SYNTAX DelayX20Us
			MAX-ACCESS read-only
			STATUS current
			DESCRIPTION
				"Indicates the input to output delay"
		::= { frs3004c02v1Entry 81 }

		-- 1.3.6.1.4.1.10106.3.101291.1.1.83
		frs3004c02v1SerialNo OBJECT-TYPE
			SYNTAX SerialNo
			MAX-ACCESS read-only
			STATUS current
			DESCRIPTION
				"Serial number"
		::= { frs3004c02v1Entry 83 }

		-- 1.3.6.1.4.1.10106.3.226401
		kbd3100p01v1 OBJECT IDENTIFIER ::= { albalaProducts 226401 }

		-- 1.3.6.1.4.1.10106.3.226401.1
		kbd3100p01v1Table  OBJECT-TYPE
			SYNTAX SEQUENCE OF Kbd3100p01v1Entry
			MAX-ACCESS not-accessible
			STATUS current
			DESCRIPTION
				"Module  KBD3100P01V1 Table"
			::= { kbd3100p01v1 1 }

		-- 1.3.6.1.4.1.10106.3.226401.1.1
		kbd3100p01v1Entry  OBJECT-TYPE
			SYNTAX Kbd3100p01v1Entry
			MAX-ACCESS not-accessible
			STATUS current
			DESCRIPTION
				"Module KBD3100P01V1 Entry"
			INDEX { kbd3100p01v1Index }
			::= { kbd3100p01v1Table 1 }

			Kbd3100p01v1Entry ::=
			SEQUENCE {
				kbd3100p01v1Index
				ModuleIndex,
				kbd3100p01v1BeepEna
				Bit0No1Yes,
				kbd3100p01v1ShowErr
				Bit0No1Yes,
				kbd3100p01v1InvertGpi1Pol
				Bit0No1Yes,
				kbd3100p01v1InvertGpi2Pol
				Bit0No1Yes,
				kbd3100p01v1InvertGpi3Pol
				Bit0No1Yes,
				kbd3100p01v1InvertGpi4Pol
				Bit0No1Yes,
				kbd3100p01v1InvertGpi5Pol
				Bit0No1Yes,
				kbd3100p01v1InvertGpi6Pol
				Bit0No1Yes,
				kbd3100p01v1InvertGpi7Pol
				Bit0No1Yes,
				kbd3100p01v1InvertGpi8Pol
				Bit0No1Yes,
				kbd3100p01v1Gpi1
				Bit0Ina1Act,
				kbd3100p01v1Gpi2
				Bit0Ina1Act,
				kbd3100p01v1Gpi3
				Bit0Ina1Act,
				kbd3100p01v1Gpi4
				Bit0Ina1Act,
				kbd3100p01v1Gpi5
				Bit0Ina1Act,
				kbd3100p01v1Gpi6
				Bit0Ina1Act,
				kbd3100p01v1Gpi7
				Bit0Ina1Act,
				kbd3100p01v1Gpi8
				Bit0Ina1Act
			 }

		-- 1.3.6.1.4.1.10106.3.101291.1.1.1
		kbd3100p01v1Index OBJECT-TYPE
			SYNTAX ModuleIndex
			MAX-ACCESS read-only
			STATUS current
			DESCRIPTION
				"Index of KBD3100P01V1 Table"
		::= { kbd3100p01v1Entry 1 }

		-- 1.3.6.1.4.1.10106.3.101291.1.1.3
		kbd3100p01v1BeepEna OBJECT-TYPE
			SYNTAX Bit0No1Yes
			MAX-ACCESS read-write
			STATUS current
			DESCRIPTION
				"Allows that the keys make a beep when pressed"
		::= { kbd3100p01v1Entry 3 }

		-- 1.3.6.1.4.1.10106.3.101291.1.1.5
		kbd3100p01v1ShowErr OBJECT-TYPE
			SYNTAX Bit0No1Yes
			MAX-ACCESS read-write
			STATUS current
			DESCRIPTION
				"Allows viewing comunication erros on LCD display"
		::= { kbd3100p01v1Entry 5 }

		-- 1.3.6.1.4.1.10106.3.101291.1.1.7
		kbd3100p01v1InvertGpi1Pol OBJECT-TYPE
			SYNTAX Bit0No1Yes
			MAX-ACCESS read-write
			STATUS current
			DESCRIPTION
				"Changes GPI1 polarity to normally closed"
		::= { kbd3100p01v1Entry 7 }

		-- 1.3.6.1.4.1.10106.3.101291.1.1.9
		kbd3100p01v1InvertGpi2Pol OBJECT-TYPE
			SYNTAX Bit0No1Yes
			MAX-ACCESS read-write
			STATUS current
			DESCRIPTION
				"Changes GPI2 polarity to normally closed"
		::= { kbd3100p01v1Entry 9 }

		-- 1.3.6.1.4.1.10106.3.101291.1.1.11
		kbd3100p01v1InvertGpi3Pol OBJECT-TYPE
			SYNTAX Bit0No1Yes
			MAX-ACCESS read-write
			STATUS current
			DESCRIPTION
				"Changes GPI3 polarity to normally closed"
		::= { kbd3100p01v1Entry 11 }

		-- 1.3.6.1.4.1.10106.3.101291.1.1.13
		kbd3100p01v1InvertGpi4Pol OBJECT-TYPE
			SYNTAX Bit0No1Yes
			MAX-ACCESS read-write
			STATUS current
			DESCRIPTION
				"Changes GPI4 polarity to normally closed"
		::= { kbd3100p01v1Entry 13 }

		-- 1.3.6.1.4.1.10106.3.101291.1.1.15
		kbd3100p01v1InvertGpi5Pol OBJECT-TYPE
			SYNTAX Bit0No1Yes
			MAX-ACCESS read-write
			STATUS current
			DESCRIPTION
				"Changes GPI5 polarity to normally closed"
		::= { kbd3100p01v1Entry 15 }

		-- 1.3.6.1.4.1.10106.3.101291.1.1.17
		kbd3100p01v1InvertGpi6Pol OBJECT-TYPE
			SYNTAX Bit0No1Yes
			MAX-ACCESS read-write
			STATUS current
			DESCRIPTION
				"Changes GPI6 polarity to normally closed"
		::= { kbd3100p01v1Entry 17 }

		-- 1.3.6.1.4.1.10106.3.101291.1.1.19
		kbd3100p01v1InvertGpi7Pol OBJECT-TYPE
			SYNTAX Bit0No1Yes
			MAX-ACCESS read-write
			STATUS current
			DESCRIPTION
				"Changes GPI7 polarity to normally closed"
		::= { kbd3100p01v1Entry 19 }

		-- 1.3.6.1.4.1.10106.3.101291.1.1.21
		kbd3100p01v1InvertGpi8Pol OBJECT-TYPE
			SYNTAX Bit0No1Yes
			MAX-ACCESS read-write
			STATUS current
			DESCRIPTION
				"Changes GPI8 polarity to normally closed"
		::= { kbd3100p01v1Entry 21 }

		-- 1.3.6.1.4.1.10106.3.101291.1.1.23
		kbd3100p01v1Gpi1 OBJECT-TYPE
			SYNTAX Bit0Ina1Act
			MAX-ACCESS read-only
			STATUS current
			DESCRIPTION
				"GPI1 status"
		::= { kbd3100p01v1Entry 23 }

		-- 1.3.6.1.4.1.10106.3.101291.1.1.25
		kbd3100p01v1Gpi2 OBJECT-TYPE
			SYNTAX Bit0Ina1Act
			MAX-ACCESS read-only
			STATUS current
			DESCRIPTION
				"GPI2 status"
		::= { kbd3100p01v1Entry 25 }

		-- 1.3.6.1.4.1.10106.3.101291.1.1.27
		kbd3100p01v1Gpi3 OBJECT-TYPE
			SYNTAX Bit0Ina1Act
			MAX-ACCESS read-only
			STATUS current
			DESCRIPTION
				"GPI3 status"
		::= { kbd3100p01v1Entry 27 }

		-- 1.3.6.1.4.1.10106.3.101291.1.1.29
		kbd3100p01v1Gpi4 OBJECT-TYPE
			SYNTAX Bit0Ina1Act
			MAX-ACCESS read-only
			STATUS current
			DESCRIPTION
				"GPI4 status"
		::= { kbd3100p01v1Entry 29 }

		-- 1.3.6.1.4.1.10106.3.101291.1.1.31
		kbd3100p01v1Gpi5 OBJECT-TYPE
			SYNTAX Bit0Ina1Act
			MAX-ACCESS read-only
			STATUS current
			DESCRIPTION
				"GPI5 status"
		::= { kbd3100p01v1Entry 31 }

		-- 1.3.6.1.4.1.10106.3.101291.1.1.33
		kbd3100p01v1Gpi6 OBJECT-TYPE
			SYNTAX Bit0Ina1Act
			MAX-ACCESS read-only
			STATUS current
			DESCRIPTION
				"GPI6 status"
		::= { kbd3100p01v1Entry 33 }

		-- 1.3.6.1.4.1.10106.3.101291.1.1.35
		kbd3100p01v1Gpi7 OBJECT-TYPE
			SYNTAX Bit0Ina1Act
			MAX-ACCESS read-only
			STATUS current
			DESCRIPTION
				"GPI7 status"
		::= { kbd3100p01v1Entry 35 }

		-- 1.3.6.1.4.1.10106.3.101291.1.1.37
		kbd3100p01v1Gpi8 OBJECT-TYPE
			SYNTAX Bit0Ina1Act
			MAX-ACCESS read-only
			STATUS current
			DESCRIPTION
				"GPI8 status"
		::= { kbd3100p01v1Entry 37 }

		-- 1.3.6.1.4.1.10106.3.229601
		dvd3001p01v1 OBJECT IDENTIFIER ::= { albalaProducts 229601 }

		-- 1.3.6.1.4.1.10106.3.229601.1
		dvd3001p01v1Table  OBJECT-TYPE
			SYNTAX SEQUENCE OF Dvd3001p01v1Entry
			MAX-ACCESS not-accessible
			STATUS current
			DESCRIPTION
				"Module  DVD3001P01V1 Table"
			::= { dvd3001p01v1 1 }

		-- 1.3.6.1.4.1.10106.3.229601.1.1
		dvd3001p01v1Entry  OBJECT-TYPE
			SYNTAX Dvd3001p01v1Entry
			MAX-ACCESS not-accessible
			STATUS current
			DESCRIPTION
				"Module DVD3001P01V1 Entry"
			INDEX { dvd3001p01v1Index }
			::= { dvd3001p01v1Table 1 }

			Dvd3001p01v1Entry ::=
			SEQUENCE {
				dvd3001p01v1Index
				ModuleIndex,
				dvd3001p01v1NoSigA
				BitFail,
				dvd3001p01v1NoSigATrapEnable
				AlarmEnable,
				dvd3001p01v1MaxEqA
				BitFail,
				dvd3001p01v1NoSigB
				BitFail,
				dvd3001p01v1NoSigBTrapEnable
				AlarmEnable,
				dvd3001p01v1MaxEqB
				BitFail,
				dvd3001p01v1CableLengthA
				CableLengthX2m,
				dvd3001p01v1CableLengthB
				CableLengthX2m
			 }

		-- 1.3.6.1.4.1.10106.3.101291.1.1.1
		dvd3001p01v1Index OBJECT-TYPE
			SYNTAX ModuleIndex
			MAX-ACCESS read-only
			STATUS current
			DESCRIPTION
				"Index of DVD3001P01V1 Table"
		::= { dvd3001p01v1Entry 1 }

		-- 1.3.6.1.4.1.10106.3.101291.1.1.3
		dvd3001p01v1NoSigA OBJECT-TYPE
			SYNTAX BitFail
			MAX-ACCESS read-only
			STATUS current
			DESCRIPTION
				"Input signal status"
		::= { dvd3001p01v1Entry 3 }

		-- 1.3.6.1.4.1.10106.3.101291.1.1.4
		dvd3001p01v1NoSigATrapEnable OBJECT-TYPE
			SYNTAX AlarmEnable
			MAX-ACCESS read-write
			STATUS current
			DESCRIPTION
				"Input signal status Trap Enable"
		::= { dvd3001p01v1Entry 4 }

		-- 1.3.6.1.4.1.10106.3.101291.1.1.5
		dvd3001p01v1MaxEqA OBJECT-TYPE
			SYNTAX BitFail
			MAX-ACCESS read-only
			STATUS current
			DESCRIPTION
				"Indicates maximum equalization"
		::= { dvd3001p01v1Entry 5 }

		-- 1.3.6.1.4.1.10106.3.101291.1.1.7
		dvd3001p01v1NoSigB OBJECT-TYPE
			SYNTAX BitFail
			MAX-ACCESS read-only
			STATUS current
			DESCRIPTION
				"Input signal status"
		::= { dvd3001p01v1Entry 7 }

		-- 1.3.6.1.4.1.10106.3.101291.1.1.8
		dvd3001p01v1NoSigBTrapEnable OBJECT-TYPE
			SYNTAX AlarmEnable
			MAX-ACCESS read-write
			STATUS current
			DESCRIPTION
				"Input signal status Trap Enable"
		::= { dvd3001p01v1Entry 8 }

		-- 1.3.6.1.4.1.10106.3.101291.1.1.9
		dvd3001p01v1MaxEqB OBJECT-TYPE
			SYNTAX BitFail
			MAX-ACCESS read-only
			STATUS current
			DESCRIPTION
				"Indicates maximum equalization"
		::= { dvd3001p01v1Entry 9 }

		-- 1.3.6.1.4.1.10106.3.101291.1.1.11
		dvd3001p01v1CableLengthA OBJECT-TYPE
			SYNTAX CableLengthX2m
			MAX-ACCESS read-only
			STATUS current
			DESCRIPTION
				"Equalized cable length"
		::= { dvd3001p01v1Entry 11 }

		-- 1.3.6.1.4.1.10106.3.101291.1.1.13
		dvd3001p01v1CableLengthB OBJECT-TYPE
			SYNTAX CableLengthX2m
			MAX-ACCESS read-only
			STATUS current
			DESCRIPTION
				"Equalized cable length"
		::= { dvd3001p01v1Entry 13 }

		-- 1.3.6.1.4.1.10106.3.232401
		frs3004c01v1 OBJECT IDENTIFIER ::= { albalaProducts 232401 }

		-- 1.3.6.1.4.1.10106.3.232401.1
		frs3004c01v1Table  OBJECT-TYPE
			SYNTAX SEQUENCE OF Frs3004c01v1Entry
			MAX-ACCESS not-accessible
			STATUS current
			DESCRIPTION
				"Module  FRS3004C01V1 Table"
			::= { frs3004c01v1 1 }

		-- 1.3.6.1.4.1.10106.3.232401.1.1
		frs3004c01v1Entry  OBJECT-TYPE
			SYNTAX Frs3004c01v1Entry
			MAX-ACCESS not-accessible
			STATUS current
			DESCRIPTION
				"Module FRS3004C01V1 Entry"
			INDEX { frs3004c01v1Index }
			::= { frs3004c01v1Table 1 }

			Frs3004c01v1Entry ::=
			SEQUENCE {
				frs3004c01v1Index
				ModuleIndex,
				frs3004c01v1RefSource
				Bit0Ana1Dig,
				frs3004c01v1FailMode
				Bit0Fre1Blk,
				frs3004c01v1SynchroMode
				Bit0Fra1Lin,
				frs3004c01v1VbiMode
				Bit0Pas1Bnk,
				frs3004c01v1HDelay1
				DelayPixel1,
				frs3004c01v1VDelay1
				DelayLines1,
				frs3004c01v1LumaGain1
				GainLin1,
				frs3004c01v1ChromaGain1
				GainLin1,
				frs3004c01v1BlackOffset1
				BlackOffset1,
				frs3004c01v1HDelay2
				DelayPixel1,
				frs3004c01v1VDelay2
				DelayLines1,
				frs3004c01v1LumaGain2
				GainLin1,
				frs3004c01v1ChromaGain2
				GainLin1,
				frs3004c01v1BlackOffset2
				BlackOffset1,
				frs3004c01v1HDelay3
				DelayPixel1,
				frs3004c01v1VDelay3
				DelayLines1,
				frs3004c01v1LumaGain3
				GainLin1,
				frs3004c01v1ChromaGain3
				GainLin1,
				frs3004c01v1BlackOffset3
				BlackOffset1,
				frs3004c01v1HDelay4
				DelayPixel1,
				frs3004c01v1VDelay4
				DelayLines1,
				frs3004c01v1LumaGain4
				GainLin1,
				frs3004c01v1ChromaGain4
				GainLin1,
				frs3004c01v1BlackOffset4
				BlackOffset1,
				frs3004c01v1NoRef
				BitFail,
				frs3004c01v1NoRefTrapEnable
				AlarmEnable,
				frs3004c01v1RefUnlock
				BitFail,
				frs3004c01v1RefUnlockTrapEnable
				AlarmEnable,
				frs3004c01v1RefEdhError
				BitFail,
				frs3004c01v1RefLines
				Bit05251625,
				frs3004c01v1NoSig1
				BitFail,
				frs3004c01v1NoSig1TrapEnable
				AlarmEnable,
				frs3004c01v1NoSig2
				BitFail,
				frs3004c01v1NoSig2TrapEnable
				AlarmEnable,
				frs3004c01v1NoSig3
				BitFail,
				frs3004c01v1NoSig3TrapEnable
				AlarmEnable,
				frs3004c01v1NoSig4
				BitFail,
				frs3004c01v1NoSig4TrapEnable
				AlarmEnable,
				frs3004c01v1EdhError1
				BitFail,
				frs3004c01v1EdhError2
				BitFail,
				frs3004c01v1EdhError3
				BitFail,
				frs3004c01v1EdhError4
				BitFail,
				frs3004c01v1Sig1Delay
				DelayX20Us,
				frs3004c01v1Sig2Delay
				DelayX20Us,
				frs3004c01v1Sig3Delay
				DelayX20Us,
				frs3004c01v1Sig4Delay
				DelayX20Us,
				frs3004c01v1SerialNo
				SerialNo
			 }

		-- 1.3.6.1.4.1.10106.3.101291.1.1.1
		frs3004c01v1Index OBJECT-TYPE
			SYNTAX ModuleIndex
			MAX-ACCESS read-only
			STATUS current
			DESCRIPTION
				"Index of FRS3004C01V1 Table"
		::= { frs3004c01v1Entry 1 }

		-- 1.3.6.1.4.1.10106.3.101291.1.1.3
		frs3004c01v1RefSource OBJECT-TYPE
			SYNTAX Bit0Ana1Dig
			MAX-ACCESS read-write
			STATUS current
			DESCRIPTION
				"Allows selecting the reference signal"
		::= { frs3004c01v1Entry 3 }

		-- 1.3.6.1.4.1.10106.3.101291.1.1.5
		frs3004c01v1FailMode OBJECT-TYPE
			SYNTAX Bit0Fre1Blk
			MAX-ACCESS read-write
			STATUS current
			DESCRIPTION
				"Allows selecting the output video signal if the input fails"
		::= { frs3004c01v1Entry 5 }

		-- 1.3.6.1.4.1.10106.3.101291.1.1.7
		frs3004c01v1SynchroMode OBJECT-TYPE
			SYNTAX Bit0Fra1Lin
			MAX-ACCESS read-write
			STATUS current
			DESCRIPTION
				"Allows selecting the synchronizing mode"
		::= { frs3004c01v1Entry 7 }

		-- 1.3.6.1.4.1.10106.3.101291.1.1.9
		frs3004c01v1VbiMode OBJECT-TYPE
			SYNTAX Bit0Pas1Bnk
			MAX-ACCESS read-write
			STATUS current
			DESCRIPTION
				"Allows selecting if the VBI is blanked"
		::= { frs3004c01v1Entry 9 }

		-- 1.3.6.1.4.1.10106.3.101291.1.1.11
		frs3004c01v1HDelay1 OBJECT-TYPE
			SYNTAX DelayPixel1
			MAX-ACCESS read-write
			STATUS current
			DESCRIPTION
				"Allows adjusting the video horizontal delay"
		::= { frs3004c01v1Entry 11 }

		-- 1.3.6.1.4.1.10106.3.101291.1.1.13
		frs3004c01v1VDelay1 OBJECT-TYPE
			SYNTAX DelayLines1
			MAX-ACCESS read-write
			STATUS current
			DESCRIPTION
				"Allows adjusting the video vertical delay"
		::= { frs3004c01v1Entry 13 }

		-- 1.3.6.1.4.1.10106.3.101291.1.1.15
		frs3004c01v1LumaGain1 OBJECT-TYPE
			SYNTAX GainLin1
			MAX-ACCESS read-write
			STATUS current
			DESCRIPTION
				"Allows adjusting the luma gain"
		::= { frs3004c01v1Entry 15 }

		-- 1.3.6.1.4.1.10106.3.101291.1.1.17
		frs3004c01v1ChromaGain1 OBJECT-TYPE
			SYNTAX GainLin1
			MAX-ACCESS read-write
			STATUS current
			DESCRIPTION
				"Allows adjusting the chorma gain"
		::= { frs3004c01v1Entry 17 }

		-- 1.3.6.1.4.1.10106.3.101291.1.1.19
		frs3004c01v1BlackOffset1 OBJECT-TYPE
			SYNTAX BlackOffset1
			MAX-ACCESS read-write
			STATUS current
			DESCRIPTION
				"Allows adjusting the black offset"
		::= { frs3004c01v1Entry 19 }

		-- 1.3.6.1.4.1.10106.3.101291.1.1.21
		frs3004c01v1HDelay2 OBJECT-TYPE
			SYNTAX DelayPixel1
			MAX-ACCESS read-write
			STATUS current
			DESCRIPTION
				"Allows adjusting the video horizontal delay"
		::= { frs3004c01v1Entry 21 }

		-- 1.3.6.1.4.1.10106.3.101291.1.1.23
		frs3004c01v1VDelay2 OBJECT-TYPE
			SYNTAX DelayLines1
			MAX-ACCESS read-write
			STATUS current
			DESCRIPTION
				"Allows adjusting the video vertical delay"
		::= { frs3004c01v1Entry 23 }

		-- 1.3.6.1.4.1.10106.3.101291.1.1.25
		frs3004c01v1LumaGain2 OBJECT-TYPE
			SYNTAX GainLin1
			MAX-ACCESS read-write
			STATUS current
			DESCRIPTION
				"Allows adjusting the luma gain"
		::= { frs3004c01v1Entry 25 }

		-- 1.3.6.1.4.1.10106.3.101291.1.1.27
		frs3004c01v1ChromaGain2 OBJECT-TYPE
			SYNTAX GainLin1
			MAX-ACCESS read-write
			STATUS current
			DESCRIPTION
				"Allows adjusting the chorma gain"
		::= { frs3004c01v1Entry 27 }

		-- 1.3.6.1.4.1.10106.3.101291.1.1.29
		frs3004c01v1BlackOffset2 OBJECT-TYPE
			SYNTAX BlackOffset1
			MAX-ACCESS read-write
			STATUS current
			DESCRIPTION
				"Allows adjusting the black offset"
		::= { frs3004c01v1Entry 29 }

		-- 1.3.6.1.4.1.10106.3.101291.1.1.31
		frs3004c01v1HDelay3 OBJECT-TYPE
			SYNTAX DelayPixel1
			MAX-ACCESS read-write
			STATUS current
			DESCRIPTION
				"Allows adjusting the video horizontal delay"
		::= { frs3004c01v1Entry 31 }

		-- 1.3.6.1.4.1.10106.3.101291.1.1.33
		frs3004c01v1VDelay3 OBJECT-TYPE
			SYNTAX DelayLines1
			MAX-ACCESS read-write
			STATUS current
			DESCRIPTION
				"Allows adjusting the video vertical delay"
		::= { frs3004c01v1Entry 33 }

		-- 1.3.6.1.4.1.10106.3.101291.1.1.35
		frs3004c01v1LumaGain3 OBJECT-TYPE
			SYNTAX GainLin1
			MAX-ACCESS read-write
			STATUS current
			DESCRIPTION
				"Allows adjusting the luma gain"
		::= { frs3004c01v1Entry 35 }

		-- 1.3.6.1.4.1.10106.3.101291.1.1.37
		frs3004c01v1ChromaGain3 OBJECT-TYPE
			SYNTAX GainLin1
			MAX-ACCESS read-write
			STATUS current
			DESCRIPTION
				"Allows adjusting the chorma gain"
		::= { frs3004c01v1Entry 37 }

		-- 1.3.6.1.4.1.10106.3.101291.1.1.39
		frs3004c01v1BlackOffset3 OBJECT-TYPE
			SYNTAX BlackOffset1
			MAX-ACCESS read-write
			STATUS current
			DESCRIPTION
				"Allows adjusting the black offset"
		::= { frs3004c01v1Entry 39 }

		-- 1.3.6.1.4.1.10106.3.101291.1.1.41
		frs3004c01v1HDelay4 OBJECT-TYPE
			SYNTAX DelayPixel1
			MAX-ACCESS read-write
			STATUS current
			DESCRIPTION
				"Allows adjusting the video horizontal delay"
		::= { frs3004c01v1Entry 41 }

		-- 1.3.6.1.4.1.10106.3.101291.1.1.43
		frs3004c01v1VDelay4 OBJECT-TYPE
			SYNTAX DelayLines1
			MAX-ACCESS read-write
			STATUS current
			DESCRIPTION
				"Allows adjusting the video vertical delay"
		::= { frs3004c01v1Entry 43 }

		-- 1.3.6.1.4.1.10106.3.101291.1.1.45
		frs3004c01v1LumaGain4 OBJECT-TYPE
			SYNTAX GainLin1
			MAX-ACCESS read-write
			STATUS current
			DESCRIPTION
				"Allows adjusting the luma gain"
		::= { frs3004c01v1Entry 45 }

		-- 1.3.6.1.4.1.10106.3.101291.1.1.47
		frs3004c01v1ChromaGain4 OBJECT-TYPE
			SYNTAX GainLin1
			MAX-ACCESS read-write
			STATUS current
			DESCRIPTION
				"Allows adjusting the chorma gain"
		::= { frs3004c01v1Entry 47 }

		-- 1.3.6.1.4.1.10106.3.101291.1.1.49
		frs3004c01v1BlackOffset4 OBJECT-TYPE
			SYNTAX BlackOffset1
			MAX-ACCESS read-write
			STATUS current
			DESCRIPTION
				"Allows adjusting the black offset"
		::= { frs3004c01v1Entry 49 }

		-- 1.3.6.1.4.1.10106.3.101291.1.1.51
		frs3004c01v1NoRef OBJECT-TYPE
			SYNTAX BitFail
			MAX-ACCESS read-only
			STATUS current
			DESCRIPTION
				"Indicates reference signal fail"
		::= { frs3004c01v1Entry 51 }

		-- 1.3.6.1.4.1.10106.3.101291.1.1.52
		frs3004c01v1NoRefTrapEnable OBJECT-TYPE
			SYNTAX AlarmEnable
			MAX-ACCESS read-write
			STATUS current
			DESCRIPTION
				"Indicates reference signal fail Trap Enable"
		::= { frs3004c01v1Entry 52 }

		-- 1.3.6.1.4.1.10106.3.101291.1.1.53
		frs3004c01v1RefUnlock OBJECT-TYPE
			SYNTAX BitFail
			MAX-ACCESS read-only
			STATUS current
			DESCRIPTION
				"Indicates reference signal unlock fail"
		::= { frs3004c01v1Entry 53 }

		-- 1.3.6.1.4.1.10106.3.101291.1.1.54
		frs3004c01v1RefUnlockTrapEnable OBJECT-TYPE
			SYNTAX AlarmEnable
			MAX-ACCESS read-write
			STATUS current
			DESCRIPTION
				"Indicates reference signal unlock fail Trap Enable"
		::= { frs3004c01v1Entry 54 }

		-- 1.3.6.1.4.1.10106.3.101291.1.1.55
		frs3004c01v1RefEdhError OBJECT-TYPE
			SYNTAX BitFail
			MAX-ACCESS read-only
			STATUS current
			DESCRIPTION
				"Indicates reference if there are EDH errors in the reference signal"
		::= { frs3004c01v1Entry 55 }

		-- 1.3.6.1.4.1.10106.3.101291.1.1.57
		frs3004c01v1RefLines OBJECT-TYPE
			SYNTAX Bit05251625
			MAX-ACCESS read-only
			STATUS current
			DESCRIPTION
				"Indicates the reference signal format"
		::= { frs3004c01v1Entry 57 }

		-- 1.3.6.1.4.1.10106.3.101291.1.1.59
		frs3004c01v1NoSig1 OBJECT-TYPE
			SYNTAX BitFail
			MAX-ACCESS read-only
			STATUS current
			DESCRIPTION
				"Indicates SDI signal fail"
		::= { frs3004c01v1Entry 59 }

		-- 1.3.6.1.4.1.10106.3.101291.1.1.60
		frs3004c01v1NoSig1TrapEnable OBJECT-TYPE
			SYNTAX AlarmEnable
			MAX-ACCESS read-write
			STATUS current
			DESCRIPTION
				"Indicates SDI signal fail Trap Enable"
		::= { frs3004c01v1Entry 60 }

		-- 1.3.6.1.4.1.10106.3.101291.1.1.61
		frs3004c01v1NoSig2 OBJECT-TYPE
			SYNTAX BitFail
			MAX-ACCESS read-only
			STATUS current
			DESCRIPTION
				"Indicates SDI signal fail"
		::= { frs3004c01v1Entry 61 }

		-- 1.3.6.1.4.1.10106.3.101291.1.1.62
		frs3004c01v1NoSig2TrapEnable OBJECT-TYPE
			SYNTAX AlarmEnable
			MAX-ACCESS read-write
			STATUS current
			DESCRIPTION
				"Indicates SDI signal fail Trap Enable"
		::= { frs3004c01v1Entry 62 }

		-- 1.3.6.1.4.1.10106.3.101291.1.1.63
		frs3004c01v1NoSig3 OBJECT-TYPE
			SYNTAX BitFail
			MAX-ACCESS read-only
			STATUS current
			DESCRIPTION
				"Indicates SDI signal fail"
		::= { frs3004c01v1Entry 63 }

		-- 1.3.6.1.4.1.10106.3.101291.1.1.64
		frs3004c01v1NoSig3TrapEnable OBJECT-TYPE
			SYNTAX AlarmEnable
			MAX-ACCESS read-write
			STATUS current
			DESCRIPTION
				"Indicates SDI signal fail Trap Enable"
		::= { frs3004c01v1Entry 64 }

		-- 1.3.6.1.4.1.10106.3.101291.1.1.65
		frs3004c01v1NoSig4 OBJECT-TYPE
			SYNTAX BitFail
			MAX-ACCESS read-only
			STATUS current
			DESCRIPTION
				"Indicates SDI signal fail"
		::= { frs3004c01v1Entry 65 }

		-- 1.3.6.1.4.1.10106.3.101291.1.1.66
		frs3004c01v1NoSig4TrapEnable OBJECT-TYPE
			SYNTAX AlarmEnable
			MAX-ACCESS read-write
			STATUS current
			DESCRIPTION
				"Indicates SDI signal fail Trap Enable"
		::= { frs3004c01v1Entry 66 }

		-- 1.3.6.1.4.1.10106.3.101291.1.1.67
		frs3004c01v1EdhError1 OBJECT-TYPE
			SYNTAX BitFail
			MAX-ACCESS read-only
			STATUS current
			DESCRIPTION
				"Indicates error in SDI signal"
		::= { frs3004c01v1Entry 67 }

		-- 1.3.6.1.4.1.10106.3.101291.1.1.69
		frs3004c01v1EdhError2 OBJECT-TYPE
			SYNTAX BitFail
			MAX-ACCESS read-only
			STATUS current
			DESCRIPTION
				"Indicates error in SDI signal"
		::= { frs3004c01v1Entry 69 }

		-- 1.3.6.1.4.1.10106.3.101291.1.1.71
		frs3004c01v1EdhError3 OBJECT-TYPE
			SYNTAX BitFail
			MAX-ACCESS read-only
			STATUS current
			DESCRIPTION
				"Indicates error in SDI signal"
		::= { frs3004c01v1Entry 71 }

		-- 1.3.6.1.4.1.10106.3.101291.1.1.73
		frs3004c01v1EdhError4 OBJECT-TYPE
			SYNTAX BitFail
			MAX-ACCESS read-only
			STATUS current
			DESCRIPTION
				"Indicates error in SDI signal"
		::= { frs3004c01v1Entry 73 }

		-- 1.3.6.1.4.1.10106.3.101291.1.1.75
		frs3004c01v1Sig1Delay OBJECT-TYPE
			SYNTAX DelayX20Us
			MAX-ACCESS read-only
			STATUS current
			DESCRIPTION
				"Indicates the input to output delay"
		::= { frs3004c01v1Entry 75 }

		-- 1.3.6.1.4.1.10106.3.101291.1.1.77
		frs3004c01v1Sig2Delay OBJECT-TYPE
			SYNTAX DelayX20Us
			MAX-ACCESS read-only
			STATUS current
			DESCRIPTION
				"Indicates the input to output delay"
		::= { frs3004c01v1Entry 77 }

		-- 1.3.6.1.4.1.10106.3.101291.1.1.79
		frs3004c01v1Sig3Delay OBJECT-TYPE
			SYNTAX DelayX20Us
			MAX-ACCESS read-only
			STATUS current
			DESCRIPTION
				"Indicates the input to output delay"
		::= { frs3004c01v1Entry 79 }

		-- 1.3.6.1.4.1.10106.3.101291.1.1.81
		frs3004c01v1Sig4Delay OBJECT-TYPE
			SYNTAX DelayX20Us
			MAX-ACCESS read-only
			STATUS current
			DESCRIPTION
				"Indicates the input to output delay"
		::= { frs3004c01v1Entry 81 }

		-- 1.3.6.1.4.1.10106.3.101291.1.1.83
		frs3004c01v1SerialNo OBJECT-TYPE
			SYNTAX SerialNo
			MAX-ACCESS read-only
			STATUS current
			DESCRIPTION
				"Serial number"
		::= { frs3004c01v1Entry 83 }

		-- 1.3.6.1.4.1.10106.3.233401
		dvd3001c02v1 OBJECT IDENTIFIER ::= { albalaProducts 233401 }

		-- 1.3.6.1.4.1.10106.3.233401.1
		dvd3001c02v1Table  OBJECT-TYPE
			SYNTAX SEQUENCE OF Dvd3001c02v1Entry
			MAX-ACCESS not-accessible
			STATUS current
			DESCRIPTION
				"Module  DVD3001C02V1 Table"
			::= { dvd3001c02v1 1 }

		-- 1.3.6.1.4.1.10106.3.233401.1.1
		dvd3001c02v1Entry  OBJECT-TYPE
			SYNTAX Dvd3001c02v1Entry
			MAX-ACCESS not-accessible
			STATUS current
			DESCRIPTION
				"Module DVD3001C02V1 Entry"
			INDEX { dvd3001c02v1Index }
			::= { dvd3001c02v1Table 1 }

			Dvd3001c02v1Entry ::=
			SEQUENCE {
				dvd3001c02v1Index
				ModuleIndex,
				dvd3001c02v1NoSigA
				BitFail,
				dvd3001c02v1NoSigATrapEnable
				AlarmEnable,
				dvd3001c02v1MaxEqA
				BitFail,
				dvd3001c02v1NoSigB
				BitFail,
				dvd3001c02v1NoSigBTrapEnable
				AlarmEnable,
				dvd3001c02v1MaxEqB
				BitFail,
				dvd3001c02v1DvdMode
				BitDistrib1,
				dvd3001c02v1CableLengthA
				CableLengthX2m,
				dvd3001c02v1CableLengthB
				CableLengthX2m,
				dvd3001c02v1SerialNo
				SerialNo
			 }

		-- 1.3.6.1.4.1.10106.3.101291.1.1.1
		dvd3001c02v1Index OBJECT-TYPE
			SYNTAX ModuleIndex
			MAX-ACCESS read-only
			STATUS current
			DESCRIPTION
				"Index of DVD3001C02V1 Table"
		::= { dvd3001c02v1Entry 1 }

		-- 1.3.6.1.4.1.10106.3.101291.1.1.3
		dvd3001c02v1NoSigA OBJECT-TYPE
			SYNTAX BitFail
			MAX-ACCESS read-only
			STATUS current
			DESCRIPTION
				"Input signal status"
		::= { dvd3001c02v1Entry 3 }

		-- 1.3.6.1.4.1.10106.3.101291.1.1.4
		dvd3001c02v1NoSigATrapEnable OBJECT-TYPE
			SYNTAX AlarmEnable
			MAX-ACCESS read-write
			STATUS current
			DESCRIPTION
				"Input signal status Trap Enable"
		::= { dvd3001c02v1Entry 4 }

		-- 1.3.6.1.4.1.10106.3.101291.1.1.5
		dvd3001c02v1MaxEqA OBJECT-TYPE
			SYNTAX BitFail
			MAX-ACCESS read-only
			STATUS current
			DESCRIPTION
				"Indicates maximum equalization"
		::= { dvd3001c02v1Entry 5 }

		-- 1.3.6.1.4.1.10106.3.101291.1.1.7
		dvd3001c02v1NoSigB OBJECT-TYPE
			SYNTAX BitFail
			MAX-ACCESS read-only
			STATUS current
			DESCRIPTION
				"Input signal status"
		::= { dvd3001c02v1Entry 7 }

		-- 1.3.6.1.4.1.10106.3.101291.1.1.8
		dvd3001c02v1NoSigBTrapEnable OBJECT-TYPE
			SYNTAX AlarmEnable
			MAX-ACCESS read-write
			STATUS current
			DESCRIPTION
				"Input signal status Trap Enable"
		::= { dvd3001c02v1Entry 8 }

		-- 1.3.6.1.4.1.10106.3.101291.1.1.9
		dvd3001c02v1MaxEqB OBJECT-TYPE
			SYNTAX BitFail
			MAX-ACCESS read-only
			STATUS current
			DESCRIPTION
				"Indicates maximum equalization"
		::= { dvd3001c02v1Entry 9 }

		-- 1.3.6.1.4.1.10106.3.101291.1.1.11
		dvd3001c02v1DvdMode OBJECT-TYPE
			SYNTAX BitDistrib1
			MAX-ACCESS read-only
			STATUS current
			DESCRIPTION
				"Operating mode"
		::= { dvd3001c02v1Entry 11 }

		-- 1.3.6.1.4.1.10106.3.101291.1.1.13
		dvd3001c02v1CableLengthA OBJECT-TYPE
			SYNTAX CableLengthX2m
			MAX-ACCESS read-only
			STATUS current
			DESCRIPTION
				"Equalized cable length"
		::= { dvd3001c02v1Entry 13 }

		-- 1.3.6.1.4.1.10106.3.101291.1.1.15
		dvd3001c02v1CableLengthB OBJECT-TYPE
			SYNTAX CableLengthX2m
			MAX-ACCESS read-only
			STATUS current
			DESCRIPTION
				"Equalized cable length"
		::= { dvd3001c02v1Entry 15 }

		-- 1.3.6.1.4.1.10106.3.101291.1.1.17
		dvd3001c02v1SerialNo OBJECT-TYPE
			SYNTAX SerialNo
			MAX-ACCESS read-only
			STATUS current
			DESCRIPTION
				"Serial number"
		::= { dvd3001c02v1Entry 17 }

		-- 1.3.6.1.4.1.10106.3.233501
		dvd3001c03v1 OBJECT IDENTIFIER ::= { albalaProducts 233501 }

		-- 1.3.6.1.4.1.10106.3.233501.1
		dvd3001c03v1Table  OBJECT-TYPE
			SYNTAX SEQUENCE OF Dvd3001c03v1Entry
			MAX-ACCESS not-accessible
			STATUS current
			DESCRIPTION
				"Module  DVD3001C03V1 Table"
			::= { dvd3001c03v1 1 }

		-- 1.3.6.1.4.1.10106.3.233501.1.1
		dvd3001c03v1Entry  OBJECT-TYPE
			SYNTAX Dvd3001c03v1Entry
			MAX-ACCESS not-accessible
			STATUS current
			DESCRIPTION
				"Module DVD3001C03V1 Entry"
			INDEX { dvd3001c03v1Index }
			::= { dvd3001c03v1Table 1 }

			Dvd3001c03v1Entry ::=
			SEQUENCE {
				dvd3001c03v1Index
				ModuleIndex,
				dvd3001c03v1NoSigA
				BitFail,
				dvd3001c03v1NoSigATrapEnable
				AlarmEnable,
				dvd3001c03v1MaxEqA
				BitFail,
				dvd3001c03v1NoSigB
				BitFail,
				dvd3001c03v1NoSigBTrapEnable
				AlarmEnable,
				dvd3001c03v1MaxEqB
				BitFail,
				dvd3001c03v1DvdMode
				BitDistrib1,
				dvd3001c03v1CableLengthA
				CableLengthX2m,
				dvd3001c03v1CableLengthB
				CableLengthX2m,
				dvd3001c03v1SerialNo
				SerialNo
			 }

		-- 1.3.6.1.4.1.10106.3.101291.1.1.1
		dvd3001c03v1Index OBJECT-TYPE
			SYNTAX ModuleIndex
			MAX-ACCESS read-only
			STATUS current
			DESCRIPTION
				"Index of DVD3001C03V1 Table"
		::= { dvd3001c03v1Entry 1 }

		-- 1.3.6.1.4.1.10106.3.101291.1.1.3
		dvd3001c03v1NoSigA OBJECT-TYPE
			SYNTAX BitFail
			MAX-ACCESS read-only
			STATUS current
			DESCRIPTION
				"Input signal status"
		::= { dvd3001c03v1Entry 3 }

		-- 1.3.6.1.4.1.10106.3.101291.1.1.4
		dvd3001c03v1NoSigATrapEnable OBJECT-TYPE
			SYNTAX AlarmEnable
			MAX-ACCESS read-write
			STATUS current
			DESCRIPTION
				"Input signal status Trap Enable"
		::= { dvd3001c03v1Entry 4 }

		-- 1.3.6.1.4.1.10106.3.101291.1.1.5
		dvd3001c03v1MaxEqA OBJECT-TYPE
			SYNTAX BitFail
			MAX-ACCESS read-only
			STATUS current
			DESCRIPTION
				"Indicates maximum equalization"
		::= { dvd3001c03v1Entry 5 }

		-- 1.3.6.1.4.1.10106.3.101291.1.1.7
		dvd3001c03v1NoSigB OBJECT-TYPE
			SYNTAX BitFail
			MAX-ACCESS read-only
			STATUS current
			DESCRIPTION
				"Input signal status"
		::= { dvd3001c03v1Entry 7 }

		-- 1.3.6.1.4.1.10106.3.101291.1.1.8
		dvd3001c03v1NoSigBTrapEnable OBJECT-TYPE
			SYNTAX AlarmEnable
			MAX-ACCESS read-write
			STATUS current
			DESCRIPTION
				"Input signal status Trap Enable"
		::= { dvd3001c03v1Entry 8 }

		-- 1.3.6.1.4.1.10106.3.101291.1.1.9
		dvd3001c03v1MaxEqB OBJECT-TYPE
			SYNTAX BitFail
			MAX-ACCESS read-only
			STATUS current
			DESCRIPTION
				"Indicates maximum equalization"
		::= { dvd3001c03v1Entry 9 }

		-- 1.3.6.1.4.1.10106.3.101291.1.1.11
		dvd3001c03v1DvdMode OBJECT-TYPE
			SYNTAX BitDistrib1
			MAX-ACCESS read-only
			STATUS current
			DESCRIPTION
				"Operating mode"
		::= { dvd3001c03v1Entry 11 }

		-- 1.3.6.1.4.1.10106.3.101291.1.1.13
		dvd3001c03v1CableLengthA OBJECT-TYPE
			SYNTAX CableLengthX2m
			MAX-ACCESS read-only
			STATUS current
			DESCRIPTION
				"Equalized cable length"
		::= { dvd3001c03v1Entry 13 }

		-- 1.3.6.1.4.1.10106.3.101291.1.1.15
		dvd3001c03v1CableLengthB OBJECT-TYPE
			SYNTAX CableLengthX2m
			MAX-ACCESS read-only
			STATUS current
			DESCRIPTION
				"Equalized cable length"
		::= { dvd3001c03v1Entry 15 }

		-- 1.3.6.1.4.1.10106.3.101291.1.1.17
		dvd3001c03v1SerialNo OBJECT-TYPE
			SYNTAX SerialNo
			MAX-ACCESS read-only
			STATUS current
			DESCRIPTION
				"Serial number"
		::= { dvd3001c03v1Entry 17 }

		-- 1.3.6.1.4.1.10106.3.234101
		dvd3001c04v1 OBJECT IDENTIFIER ::= { albalaProducts 234101 }

		-- 1.3.6.1.4.1.10106.3.234101.1
		dvd3001c04v1Table  OBJECT-TYPE
			SYNTAX SEQUENCE OF Dvd3001c04v1Entry
			MAX-ACCESS not-accessible
			STATUS current
			DESCRIPTION
				"Module  DVD3001C04V1 Table"
			::= { dvd3001c04v1 1 }

		-- 1.3.6.1.4.1.10106.3.234101.1.1
		dvd3001c04v1Entry  OBJECT-TYPE
			SYNTAX Dvd3001c04v1Entry
			MAX-ACCESS not-accessible
			STATUS current
			DESCRIPTION
				"Module DVD3001C04V1 Entry"
			INDEX { dvd3001c04v1Index }
			::= { dvd3001c04v1Table 1 }

			Dvd3001c04v1Entry ::=
			SEQUENCE {
				dvd3001c04v1Index
				ModuleIndex,
				dvd3001c04v1NoSigA
				BitFail,
				dvd3001c04v1NoSigATrapEnable
				AlarmEnable,
				dvd3001c04v1MaxEqA
				BitFail,
				dvd3001c04v1CableLengthA
				CableLengthX2m,
				dvd3001c04v1SerialNo
				SerialNo
			 }

		-- 1.3.6.1.4.1.10106.3.101291.1.1.1
		dvd3001c04v1Index OBJECT-TYPE
			SYNTAX ModuleIndex
			MAX-ACCESS read-only
			STATUS current
			DESCRIPTION
				"Index of DVD3001C04V1 Table"
		::= { dvd3001c04v1Entry 1 }

		-- 1.3.6.1.4.1.10106.3.101291.1.1.3
		dvd3001c04v1NoSigA OBJECT-TYPE
			SYNTAX BitFail
			MAX-ACCESS read-only
			STATUS current
			DESCRIPTION
				"Input signal status"
		::= { dvd3001c04v1Entry 3 }

		-- 1.3.6.1.4.1.10106.3.101291.1.1.4
		dvd3001c04v1NoSigATrapEnable OBJECT-TYPE
			SYNTAX AlarmEnable
			MAX-ACCESS read-write
			STATUS current
			DESCRIPTION
				"Input signal status Trap Enable"
		::= { dvd3001c04v1Entry 4 }

		-- 1.3.6.1.4.1.10106.3.101291.1.1.5
		dvd3001c04v1MaxEqA OBJECT-TYPE
			SYNTAX BitFail
			MAX-ACCESS read-only
			STATUS current
			DESCRIPTION
				"Indicates maximum equalization"
		::= { dvd3001c04v1Entry 5 }

		-- 1.3.6.1.4.1.10106.3.101291.1.1.7
		dvd3001c04v1CableLengthA OBJECT-TYPE
			SYNTAX CableLengthX2m
			MAX-ACCESS read-only
			STATUS current
			DESCRIPTION
				"Equalized cable length"
		::= { dvd3001c04v1Entry 7 }

		-- 1.3.6.1.4.1.10106.3.101291.1.1.9
		dvd3001c04v1SerialNo OBJECT-TYPE
			SYNTAX SerialNo
			MAX-ACCESS read-only
			STATUS current
			DESCRIPTION
				"Serial number"
		::= { dvd3001c04v1Entry 9 }

		-- 1.3.6.1.4.1.10106.3.234201
		dvd3001c05v1 OBJECT IDENTIFIER ::= { albalaProducts 234201 }

		-- 1.3.6.1.4.1.10106.3.234201.1
		dvd3001c05v1Table  OBJECT-TYPE
			SYNTAX SEQUENCE OF Dvd3001c05v1Entry
			MAX-ACCESS not-accessible
			STATUS current
			DESCRIPTION
				"Module  DVD3001C05V1 Table"
			::= { dvd3001c05v1 1 }

		-- 1.3.6.1.4.1.10106.3.234201.1.1
		dvd3001c05v1Entry  OBJECT-TYPE
			SYNTAX Dvd3001c05v1Entry
			MAX-ACCESS not-accessible
			STATUS current
			DESCRIPTION
				"Module DVD3001C05V1 Entry"
			INDEX { dvd3001c05v1Index }
			::= { dvd3001c05v1Table 1 }

			Dvd3001c05v1Entry ::=
			SEQUENCE {
				dvd3001c05v1Index
				ModuleIndex,
				dvd3001c05v1NoSigA
				BitFail,
				dvd3001c05v1NoSigATrapEnable
				AlarmEnable,
				dvd3001c05v1MaxEqA
				BitFail,
				dvd3001c05v1CableLengthA
				CableLengthX2m,
				dvd3001c05v1SerialNo
				SerialNo
			 }

		-- 1.3.6.1.4.1.10106.3.101291.1.1.1
		dvd3001c05v1Index OBJECT-TYPE
			SYNTAX ModuleIndex
			MAX-ACCESS read-only
			STATUS current
			DESCRIPTION
				"Index of DVD3001C05V1 Table"
		::= { dvd3001c05v1Entry 1 }

		-- 1.3.6.1.4.1.10106.3.101291.1.1.3
		dvd3001c05v1NoSigA OBJECT-TYPE
			SYNTAX BitFail
			MAX-ACCESS read-only
			STATUS current
			DESCRIPTION
				"Input signal status"
		::= { dvd3001c05v1Entry 3 }

		-- 1.3.6.1.4.1.10106.3.101291.1.1.4
		dvd3001c05v1NoSigATrapEnable OBJECT-TYPE
			SYNTAX AlarmEnable
			MAX-ACCESS read-write
			STATUS current
			DESCRIPTION
				"Input signal status Trap Enable"
		::= { dvd3001c05v1Entry 4 }

		-- 1.3.6.1.4.1.10106.3.101291.1.1.5
		dvd3001c05v1MaxEqA OBJECT-TYPE
			SYNTAX BitFail
			MAX-ACCESS read-only
			STATUS current
			DESCRIPTION
				"Indicates maximum equalization"
		::= { dvd3001c05v1Entry 5 }

		-- 1.3.6.1.4.1.10106.3.101291.1.1.7
		dvd3001c05v1CableLengthA OBJECT-TYPE
			SYNTAX CableLengthX2m
			MAX-ACCESS read-only
			STATUS current
			DESCRIPTION
				"Equalized cable length"
		::= { dvd3001c05v1Entry 7 }

		-- 1.3.6.1.4.1.10106.3.101291.1.1.9
		dvd3001c05v1SerialNo OBJECT-TYPE
			SYNTAX SerialNo
			MAX-ACCESS read-only
			STATUS current
			DESCRIPTION
				"Serial number"
		::= { dvd3001c05v1Entry 9 }

		-- 1.3.6.1.4.1.10106.3.238701
		sdr3000p02v1 OBJECT IDENTIFIER ::= { albalaProducts 238701 }

		-- 1.3.6.1.4.1.10106.3.238701.1
		sdr3000p02v1Table  OBJECT-TYPE
			SYNTAX SEQUENCE OF Sdr3000p02v1Entry
			MAX-ACCESS not-accessible
			STATUS current
			DESCRIPTION
				"Module  SDR3000P02V1 Table"
			::= { sdr3000p02v1 1 }

		-- 1.3.6.1.4.1.10106.3.238701.1.1
		sdr3000p02v1Entry  OBJECT-TYPE
			SYNTAX Sdr3000p02v1Entry
			MAX-ACCESS not-accessible
			STATUS current
			DESCRIPTION
				"Module SDR3000P02V1 Entry"
			INDEX { sdr3000p02v1Index }
			::= { sdr3000p02v1Table 1 }

			Sdr3000p02v1Entry ::=
			SEQUENCE {
				sdr3000p02v1Index
				ModuleIndex,
				sdr3000p02v1NoSigA
				BitFail,
				sdr3000p02v1NoSigATrapEnable
				AlarmEnable,
				sdr3000p02v1NoSigB
				BitFail,
				sdr3000p02v1NoSigBTrapEnable
				AlarmEnable,
				sdr3000p02v1RxPowerA
				Uint8,
				sdr3000p02v1RxPowerB
				Uint8
			 }

		-- 1.3.6.1.4.1.10106.3.101291.1.1.1
		sdr3000p02v1Index OBJECT-TYPE
			SYNTAX ModuleIndex
			MAX-ACCESS read-only
			STATUS current
			DESCRIPTION
				"Index of SDR3000P02V1 Table"
		::= { sdr3000p02v1Entry 1 }

		-- 1.3.6.1.4.1.10106.3.101291.1.1.3
		sdr3000p02v1NoSigA OBJECT-TYPE
			SYNTAX BitFail
			MAX-ACCESS read-only
			STATUS current
			DESCRIPTION
				"Input signal status"
		::= { sdr3000p02v1Entry 3 }

		-- 1.3.6.1.4.1.10106.3.101291.1.1.4
		sdr3000p02v1NoSigATrapEnable OBJECT-TYPE
			SYNTAX AlarmEnable
			MAX-ACCESS read-write
			STATUS current
			DESCRIPTION
				"Input signal status Trap Enable"
		::= { sdr3000p02v1Entry 4 }

		-- 1.3.6.1.4.1.10106.3.101291.1.1.5
		sdr3000p02v1NoSigB OBJECT-TYPE
			SYNTAX BitFail
			MAX-ACCESS read-only
			STATUS current
			DESCRIPTION
				"Input signal status"
		::= { sdr3000p02v1Entry 5 }

		-- 1.3.6.1.4.1.10106.3.101291.1.1.6
		sdr3000p02v1NoSigBTrapEnable OBJECT-TYPE
			SYNTAX AlarmEnable
			MAX-ACCESS read-write
			STATUS current
			DESCRIPTION
				"Input signal status Trap Enable"
		::= { sdr3000p02v1Entry 6 }

		-- 1.3.6.1.4.1.10106.3.101291.1.1.7
		sdr3000p02v1RxPowerA OBJECT-TYPE
			SYNTAX Uint8
			MAX-ACCESS read-only
			STATUS current
			DESCRIPTION
				"Inidcates the RX power"
		::= { sdr3000p02v1Entry 7 }

		-- 1.3.6.1.4.1.10106.3.101291.1.1.9
		sdr3000p02v1RxPowerB OBJECT-TYPE
			SYNTAX Uint8
			MAX-ACCESS read-only
			STATUS current
			DESCRIPTION
				"Inidcates the RX power"
		::= { sdr3000p02v1Entry 9 }

		-- 1.3.6.1.4.1.10106.3.241501
		asw3000c01v1 OBJECT IDENTIFIER ::= { albalaProducts 241501 }

		-- 1.3.6.1.4.1.10106.3.241501.1
		asw3000c01v1Table  OBJECT-TYPE
			SYNTAX SEQUENCE OF Asw3000c01v1Entry
			MAX-ACCESS not-accessible
			STATUS current
			DESCRIPTION
				"Module  ASW3000C01V1 Table"
			::= { asw3000c01v1 1 }

		-- 1.3.6.1.4.1.10106.3.241501.1.1
		asw3000c01v1Entry  OBJECT-TYPE
			SYNTAX Asw3000c01v1Entry
			MAX-ACCESS not-accessible
			STATUS current
			DESCRIPTION
				"Module ASW3000C01V1 Entry"
			INDEX { asw3000c01v1Index }
			::= { asw3000c01v1Table 1 }

			Asw3000c01v1Entry ::=
			SEQUENCE {
				asw3000c01v1Index
				ModuleIndex,
				asw3000c01v1Mode
				ChgOverMode2,
				asw3000c01v1ModeTrapEnable
				AlarmEnable,
				asw3000c01v1Buzzer
				BitMask,
				asw3000c01v1Input
				ChgOverInput2,
				asw3000c01v1InputTrapEnable
				AlarmEnable,
				asw3000c01v1GpiMask
				BitMask,
				asw3000c01v1PresenceMask
				BitMask,
				asw3000c01v1SyncLMask
				BitMask,
				asw3000c01v1SyncBMask
				BitMask,
				asw3000c01v1PatErrMask
				BitMask,
				asw3000c01v1PatCcMask
				BitMask,
				asw3000c01v1BitrateMask
				BitMask,
				asw3000c01v1NullPckMask
				BitMask,
				asw3000c01v1BitrateMin
				Bitrate2kbps,
				asw3000c01v1BitrateMax
				Bitrate2kbps,
				asw3000c01v1PckNullMin
				PckNullRate1,
				asw3000c01v1PckNullMax
				PckNullRate1,
				asw3000c01v1ActTime
				TimeX50Ms,
				asw3000c01v1RecTime
				TimeS2,
				asw3000c01v1PatTimeout
				TimeX40Ms,
				asw3000c01v1InvertPriority
				Bit0No1Yes,
				asw3000c01v1MainPckBytes
				Bit02041188,
				asw3000c01v1MainGlobalFail
				BitFail,
				asw3000c01v1MainGlobalFailTrapEnable
				AlarmEnable,
				asw3000c01v1ResPckBytes
				Bit02041188,
				asw3000c01v1ResGlobalFail
				BitFail,
				asw3000c01v1ResGlobalFailTrapEnable
				AlarmEnable,
				asw3000c01v1MainGpiFail
				BitFail,
				asw3000c01v1MainGpiFailTrapEnable
				AlarmEnable,
				asw3000c01v1MainPresFail
				BitFail,
				asw3000c01v1MainPresFailTrapEnable
				AlarmEnable,
				asw3000c01v1MainSyncLFail
				BitFail,
				asw3000c01v1MainSyncLFailTrapEnable
				AlarmEnable,
				asw3000c01v1MainSyncBFail
				BitFail,
				asw3000c01v1MainSyncBFailTrapEnable
				AlarmEnable,
				asw3000c01v1MainPatErFail
				BitFail,
				asw3000c01v1MainPatErFailTrapEnable
				AlarmEnable,
				asw3000c01v1MainPatCcFail
				BitFail,
				asw3000c01v1MainPatCcFailTrapEnable
				AlarmEnable,
				asw3000c01v1MainTraffFail
				BitFail,
				asw3000c01v1MainTraffFailTrapEnable
				AlarmEnable,
				asw3000c01v1MainNullPFail
				BitFail,
				asw3000c01v1MainNullPFailTrapEnable
				AlarmEnable,
				asw3000c01v1ResGpiFail
				BitFail,
				asw3000c01v1ResGpiFailTrapEnable
				AlarmEnable,
				asw3000c01v1ResPresFail
				BitFail,
				asw3000c01v1ResPresFailTrapEnable
				AlarmEnable,
				asw3000c01v1ResSyncLFail
				BitFail,
				asw3000c01v1ResSyncLFailTrapEnable
				AlarmEnable,
				asw3000c01v1ResSyncBFail
				BitFail,
				asw3000c01v1ResSyncBFailTrapEnable
				AlarmEnable,
				asw3000c01v1ResPatErFail
				BitFail,
				asw3000c01v1ResPatErFailTrapEnable
				AlarmEnable,
				asw3000c01v1ResPatCcFail
				BitFail,
				asw3000c01v1ResPatCcFailTrapEnable
				AlarmEnable,
				asw3000c01v1ResTraffFail
				BitFail,
				asw3000c01v1ResTraffFailTrapEnable
				AlarmEnable,
				asw3000c01v1ResNullPFail
				BitFail,
				asw3000c01v1ResNullPFailTrapEnable
				AlarmEnable,
				asw3000c01v1MainBitrate
				Bitrate2kbps,
				asw3000c01v1ResBitrate
				Bitrate2kbps,
				asw3000c01v1MainPckNull
				PckNullRate1,
				asw3000c01v1ResPckNull
				PckNullRate1,
				asw3000c01v1SerialNo
				SerialNo
			 }

		-- 1.3.6.1.4.1.10106.3.101291.1.1.1
		asw3000c01v1Index OBJECT-TYPE
			SYNTAX ModuleIndex
			MAX-ACCESS read-only
			STATUS current
			DESCRIPTION
				"Index of ASW3000C01V1 Table"
		::= { asw3000c01v1Entry 1 }

		-- 1.3.6.1.4.1.10106.3.101291.1.1.3
		asw3000c01v1Mode OBJECT-TYPE
			SYNTAX ChgOverMode2
			MAX-ACCESS read-write
			STATUS current
			DESCRIPTION
				"Allows selecting the switching mode"
		::= { asw3000c01v1Entry 3 }

		-- 1.3.6.1.4.1.10106.3.101291.1.1.4
		asw3000c01v1ModeTrapEnable OBJECT-TYPE
			SYNTAX AlarmEnable
			MAX-ACCESS read-write
			STATUS current
			DESCRIPTION
				"Allows selecting the switching mode Trap Enable"
		::= { asw3000c01v1Entry 4 }

		-- 1.3.6.1.4.1.10106.3.101291.1.1.5
		asw3000c01v1Buzzer OBJECT-TYPE
			SYNTAX BitMask
			MAX-ACCESS read-write
			STATUS current
			DESCRIPTION
				"Allows buzzer operation"
		::= { asw3000c01v1Entry 5 }

		-- 1.3.6.1.4.1.10106.3.101291.1.1.7
		asw3000c01v1Input OBJECT-TYPE
			SYNTAX ChgOverInput2
			MAX-ACCESS read-write
			STATUS current
			DESCRIPTION
				"Selected input"
		::= { asw3000c01v1Entry 7 }

		-- 1.3.6.1.4.1.10106.3.101291.1.1.8
		asw3000c01v1InputTrapEnable OBJECT-TYPE
			SYNTAX AlarmEnable
			MAX-ACCESS read-write
			STATUS current
			DESCRIPTION
				"Selected input Trap Enable"
		::= { asw3000c01v1Entry 8 }

		-- 1.3.6.1.4.1.10106.3.101291.1.1.9
		asw3000c01v1GpiMask OBJECT-TYPE
			SYNTAX BitMask
			MAX-ACCESS read-write
			STATUS current
			DESCRIPTION
				"Allows masking fail of GPIs"
		::= { asw3000c01v1Entry 9 }

		-- 1.3.6.1.4.1.10106.3.101291.1.1.11
		asw3000c01v1PresenceMask OBJECT-TYPE
			SYNTAX BitMask
			MAX-ACCESS read-write
			STATUS current
			DESCRIPTION
				"Allows masking fail of signal presence"
		::= { asw3000c01v1Entry 11 }

		-- 1.3.6.1.4.1.10106.3.101291.1.1.13
		asw3000c01v1SyncLMask OBJECT-TYPE
			SYNTAX BitMask
			MAX-ACCESS read-write
			STATUS current
			DESCRIPTION
				"Allows masking fail of sync loss"
		::= { asw3000c01v1Entry 13 }

		-- 1.3.6.1.4.1.10106.3.101291.1.1.15
		asw3000c01v1SyncBMask OBJECT-TYPE
			SYNTAX BitMask
			MAX-ACCESS read-write
			STATUS current
			DESCRIPTION
				"Allows masking fail of sync byte error"
		::= { asw3000c01v1Entry 15 }

		-- 1.3.6.1.4.1.10106.3.101291.1.1.17
		asw3000c01v1PatErrMask OBJECT-TYPE
			SYNTAX BitMask
			MAX-ACCESS read-write
			STATUS current
			DESCRIPTION
				"Allows masking fail of PAT error"
		::= { asw3000c01v1Entry 17 }

		-- 1.3.6.1.4.1.10106.3.101291.1.1.19
		asw3000c01v1PatCcMask OBJECT-TYPE
			SYNTAX BitMask
			MAX-ACCESS read-write
			STATUS current
			DESCRIPTION
				"Allows masking fail of PAT continuity counter"
		::= { asw3000c01v1Entry 19 }

		-- 1.3.6.1.4.1.10106.3.101291.1.1.21
		asw3000c01v1BitrateMask OBJECT-TYPE
			SYNTAX BitMask
			MAX-ACCESS read-write
			STATUS current
			DESCRIPTION
				"Allows masking fail of out of range bitrate"
		::= { asw3000c01v1Entry 21 }

		-- 1.3.6.1.4.1.10106.3.101291.1.1.23
		asw3000c01v1NullPckMask OBJECT-TYPE
			SYNTAX BitMask
			MAX-ACCESS read-write
			STATUS current
			DESCRIPTION
				"Allows masking fail of null packet ratio"
		::= { asw3000c01v1Entry 23 }

		-- 1.3.6.1.4.1.10106.3.101291.1.1.25
		asw3000c01v1BitrateMin OBJECT-TYPE
			SYNTAX Bitrate2kbps
			MAX-ACCESS read-write
			STATUS current
			DESCRIPTION
				"Lower bitrate limit"
		::= { asw3000c01v1Entry 25 }

		-- 1.3.6.1.4.1.10106.3.101291.1.1.27
		asw3000c01v1BitrateMax OBJECT-TYPE
			SYNTAX Bitrate2kbps
			MAX-ACCESS read-write
			STATUS current
			DESCRIPTION
				"Upper bitrate limit"
		::= { asw3000c01v1Entry 27 }

		-- 1.3.6.1.4.1.10106.3.101291.1.1.29
		asw3000c01v1PckNullMin OBJECT-TYPE
			SYNTAX PckNullRate1
			MAX-ACCESS read-write
			STATUS current
			DESCRIPTION
				"Lower packet null ratio limit"
		::= { asw3000c01v1Entry 29 }

		-- 1.3.6.1.4.1.10106.3.101291.1.1.31
		asw3000c01v1PckNullMax OBJECT-TYPE
			SYNTAX PckNullRate1
			MAX-ACCESS read-write
			STATUS current
			DESCRIPTION
				"Upper packet null ratio limit"
		::= { asw3000c01v1Entry 31 }

		-- 1.3.6.1.4.1.10106.3.101291.1.1.33
		asw3000c01v1ActTime OBJECT-TYPE
			SYNTAX TimeX50Ms
			MAX-ACCESS read-write
			STATUS current
			DESCRIPTION
				"Time that the global fail must be set before switching"
		::= { asw3000c01v1Entry 33 }

		-- 1.3.6.1.4.1.10106.3.101291.1.1.35
		asw3000c01v1RecTime OBJECT-TYPE
			SYNTAX TimeS2
			MAX-ACCESS read-write
			STATUS current
			DESCRIPTION
				"Time that the global fail must be reset before switching"
		::= { asw3000c01v1Entry 35 }

		-- 1.3.6.1.4.1.10106.3.101291.1.1.37
		asw3000c01v1PatTimeout OBJECT-TYPE
			SYNTAX TimeX40Ms
			MAX-ACCESS read-write
			STATUS current
			DESCRIPTION
				"Minimum time between PAT occurrences"
		::= { asw3000c01v1Entry 37 }

		-- 1.3.6.1.4.1.10106.3.101291.1.1.39
		asw3000c01v1InvertPriority OBJECT-TYPE
			SYNTAX Bit0No1Yes
			MAX-ACCESS read-write
			STATUS current
			DESCRIPTION
				"Allows changing the input priority to RES-MAIN"
		::= { asw3000c01v1Entry 39 }

		-- 1.3.6.1.4.1.10106.3.101291.1.1.41
		asw3000c01v1MainPckBytes OBJECT-TYPE
			SYNTAX Bit02041188
			MAX-ACCESS read-only
			STATUS current
			DESCRIPTION
				"Number of bytes in main input packets"
		::= { asw3000c01v1Entry 41 }

		-- 1.3.6.1.4.1.10106.3.101291.1.1.43
		asw3000c01v1MainGlobalFail OBJECT-TYPE
			SYNTAX BitFail
			MAX-ACCESS read-only
			STATUS current
			DESCRIPTION
				"Main input global (any kind) fail status"
		::= { asw3000c01v1Entry 43 }

		-- 1.3.6.1.4.1.10106.3.101291.1.1.44
		asw3000c01v1MainGlobalFailTrapEnable OBJECT-TYPE
			SYNTAX AlarmEnable
			MAX-ACCESS read-write
			STATUS current
			DESCRIPTION
				"Main input global (any kind) fail status Trap Enable"
		::= { asw3000c01v1Entry 44 }

		-- 1.3.6.1.4.1.10106.3.101291.1.1.45
		asw3000c01v1ResPckBytes OBJECT-TYPE
			SYNTAX Bit02041188
			MAX-ACCESS read-only
			STATUS current
			DESCRIPTION
				"Number of bytes in reserve input packets"
		::= { asw3000c01v1Entry 45 }

		-- 1.3.6.1.4.1.10106.3.101291.1.1.47
		asw3000c01v1ResGlobalFail OBJECT-TYPE
			SYNTAX BitFail
			MAX-ACCESS read-only
			STATUS current
			DESCRIPTION
				"Reserve input global (any kind) fail status"
		::= { asw3000c01v1Entry 47 }

		-- 1.3.6.1.4.1.10106.3.101291.1.1.48
		asw3000c01v1ResGlobalFailTrapEnable OBJECT-TYPE
			SYNTAX AlarmEnable
			MAX-ACCESS read-write
			STATUS current
			DESCRIPTION
				"Reserve input global (any kind) fail status Trap Enable"
		::= { asw3000c01v1Entry 48 }

		-- 1.3.6.1.4.1.10106.3.101291.1.1.49
		asw3000c01v1MainGpiFail OBJECT-TYPE
			SYNTAX BitFail
			MAX-ACCESS read-only
			STATUS current
			DESCRIPTION
				"Main external fail (GPI) status"
		::= { asw3000c01v1Entry 49 }

		-- 1.3.6.1.4.1.10106.3.101291.1.1.50
		asw3000c01v1MainGpiFailTrapEnable OBJECT-TYPE
			SYNTAX AlarmEnable
			MAX-ACCESS read-write
			STATUS current
			DESCRIPTION
				"Main external fail (GPI) status Trap Enable"
		::= { asw3000c01v1Entry 50 }

		-- 1.3.6.1.4.1.10106.3.101291.1.1.51
		asw3000c01v1MainPresFail OBJECT-TYPE
			SYNTAX BitFail
			MAX-ACCESS read-only
			STATUS current
			DESCRIPTION
				"Main signal presence status"
		::= { asw3000c01v1Entry 51 }

		-- 1.3.6.1.4.1.10106.3.101291.1.1.52
		asw3000c01v1MainPresFailTrapEnable OBJECT-TYPE
			SYNTAX AlarmEnable
			MAX-ACCESS read-write
			STATUS current
			DESCRIPTION
				"Main signal presence status Trap Enable"
		::= { asw3000c01v1Entry 52 }

		-- 1.3.6.1.4.1.10106.3.101291.1.1.53
		asw3000c01v1MainSyncLFail OBJECT-TYPE
			SYNTAX BitFail
			MAX-ACCESS read-only
			STATUS current
			DESCRIPTION
				"Main TS sync status"
		::= { asw3000c01v1Entry 53 }

		-- 1.3.6.1.4.1.10106.3.101291.1.1.54
		asw3000c01v1MainSyncLFailTrapEnable OBJECT-TYPE
			SYNTAX AlarmEnable
			MAX-ACCESS read-write
			STATUS current
			DESCRIPTION
				"Main TS sync status Trap Enable"
		::= { asw3000c01v1Entry 54 }

		-- 1.3.6.1.4.1.10106.3.101291.1.1.55
		asw3000c01v1MainSyncBFail OBJECT-TYPE
			SYNTAX BitFail
			MAX-ACCESS read-only
			STATUS current
			DESCRIPTION
				"Main sync byte presence status"
		::= { asw3000c01v1Entry 55 }

		-- 1.3.6.1.4.1.10106.3.101291.1.1.56
		asw3000c01v1MainSyncBFailTrapEnable OBJECT-TYPE
			SYNTAX AlarmEnable
			MAX-ACCESS read-write
			STATUS current
			DESCRIPTION
				"Main sync byte presence status Trap Enable"
		::= { asw3000c01v1Entry 56 }

		-- 1.3.6.1.4.1.10106.3.101291.1.1.57
		asw3000c01v1MainPatErFail OBJECT-TYPE
			SYNTAX BitFail
			MAX-ACCESS read-only
			STATUS current
			DESCRIPTION
				"Main PAT status"
		::= { asw3000c01v1Entry 57 }

		-- 1.3.6.1.4.1.10106.3.101291.1.1.58
		asw3000c01v1MainPatErFailTrapEnable OBJECT-TYPE
			SYNTAX AlarmEnable
			MAX-ACCESS read-write
			STATUS current
			DESCRIPTION
				"Main PAT status Trap Enable"
		::= { asw3000c01v1Entry 58 }

		-- 1.3.6.1.4.1.10106.3.101291.1.1.59
		asw3000c01v1MainPatCcFail OBJECT-TYPE
			SYNTAX BitFail
			MAX-ACCESS read-only
			STATUS current
			DESCRIPTION
				"Main PAT continuity counter status"
		::= { asw3000c01v1Entry 59 }

		-- 1.3.6.1.4.1.10106.3.101291.1.1.60
		asw3000c01v1MainPatCcFailTrapEnable OBJECT-TYPE
			SYNTAX AlarmEnable
			MAX-ACCESS read-write
			STATUS current
			DESCRIPTION
				"Main PAT continuity counter status Trap Enable"
		::= { asw3000c01v1Entry 60 }

		-- 1.3.6.1.4.1.10106.3.101291.1.1.61
		asw3000c01v1MainTraffFail OBJECT-TYPE
			SYNTAX BitFail
			MAX-ACCESS read-only
			STATUS current
			DESCRIPTION
				"Main bitrate status"
		::= { asw3000c01v1Entry 61 }

		-- 1.3.6.1.4.1.10106.3.101291.1.1.62
		asw3000c01v1MainTraffFailTrapEnable OBJECT-TYPE
			SYNTAX AlarmEnable
			MAX-ACCESS read-write
			STATUS current
			DESCRIPTION
				"Main bitrate status Trap Enable"
		::= { asw3000c01v1Entry 62 }

		-- 1.3.6.1.4.1.10106.3.101291.1.1.63
		asw3000c01v1MainNullPFail OBJECT-TYPE
			SYNTAX BitFail
			MAX-ACCESS read-only
			STATUS current
			DESCRIPTION
				"Main null packet rate status"
		::= { asw3000c01v1Entry 63 }

		-- 1.3.6.1.4.1.10106.3.101291.1.1.64
		asw3000c01v1MainNullPFailTrapEnable OBJECT-TYPE
			SYNTAX AlarmEnable
			MAX-ACCESS read-write
			STATUS current
			DESCRIPTION
				"Main null packet rate status Trap Enable"
		::= { asw3000c01v1Entry 64 }

		-- 1.3.6.1.4.1.10106.3.101291.1.1.65
		asw3000c01v1ResGpiFail OBJECT-TYPE
			SYNTAX BitFail
			MAX-ACCESS read-only
			STATUS current
			DESCRIPTION
				"Main external fail (GPI) status"
		::= { asw3000c01v1Entry 65 }

		-- 1.3.6.1.4.1.10106.3.101291.1.1.66
		asw3000c01v1ResGpiFailTrapEnable OBJECT-TYPE
			SYNTAX AlarmEnable
			MAX-ACCESS read-write
			STATUS current
			DESCRIPTION
				"Main external fail (GPI) status Trap Enable"
		::= { asw3000c01v1Entry 66 }

		-- 1.3.6.1.4.1.10106.3.101291.1.1.67
		asw3000c01v1ResPresFail OBJECT-TYPE
			SYNTAX BitFail
			MAX-ACCESS read-only
			STATUS current
			DESCRIPTION
				"Main signal presence status"
		::= { asw3000c01v1Entry 67 }

		-- 1.3.6.1.4.1.10106.3.101291.1.1.68
		asw3000c01v1ResPresFailTrapEnable OBJECT-TYPE
			SYNTAX AlarmEnable
			MAX-ACCESS read-write
			STATUS current
			DESCRIPTION
				"Main signal presence status Trap Enable"
		::= { asw3000c01v1Entry 68 }

		-- 1.3.6.1.4.1.10106.3.101291.1.1.69
		asw3000c01v1ResSyncLFail OBJECT-TYPE
			SYNTAX BitFail
			MAX-ACCESS read-only
			STATUS current
			DESCRIPTION
				"Main TS sync status"
		::= { asw3000c01v1Entry 69 }

		-- 1.3.6.1.4.1.10106.3.101291.1.1.70
		asw3000c01v1ResSyncLFailTrapEnable OBJECT-TYPE
			SYNTAX AlarmEnable
			MAX-ACCESS read-write
			STATUS current
			DESCRIPTION
				"Main TS sync status Trap Enable"
		::= { asw3000c01v1Entry 70 }

		-- 1.3.6.1.4.1.10106.3.101291.1.1.71
		asw3000c01v1ResSyncBFail OBJECT-TYPE
			SYNTAX BitFail
			MAX-ACCESS read-only
			STATUS current
			DESCRIPTION
				"Main sync byte presence status"
		::= { asw3000c01v1Entry 71 }

		-- 1.3.6.1.4.1.10106.3.101291.1.1.72
		asw3000c01v1ResSyncBFailTrapEnable OBJECT-TYPE
			SYNTAX AlarmEnable
			MAX-ACCESS read-write
			STATUS current
			DESCRIPTION
				"Main sync byte presence status Trap Enable"
		::= { asw3000c01v1Entry 72 }

		-- 1.3.6.1.4.1.10106.3.101291.1.1.73
		asw3000c01v1ResPatErFail OBJECT-TYPE
			SYNTAX BitFail
			MAX-ACCESS read-only
			STATUS current
			DESCRIPTION
				"Main PAT status"
		::= { asw3000c01v1Entry 73 }

		-- 1.3.6.1.4.1.10106.3.101291.1.1.74
		asw3000c01v1ResPatErFailTrapEnable OBJECT-TYPE
			SYNTAX AlarmEnable
			MAX-ACCESS read-write
			STATUS current
			DESCRIPTION
				"Main PAT status Trap Enable"
		::= { asw3000c01v1Entry 74 }

		-- 1.3.6.1.4.1.10106.3.101291.1.1.75
		asw3000c01v1ResPatCcFail OBJECT-TYPE
			SYNTAX BitFail
			MAX-ACCESS read-only
			STATUS current
			DESCRIPTION
				"Main PAT continuity counter status"
		::= { asw3000c01v1Entry 75 }

		-- 1.3.6.1.4.1.10106.3.101291.1.1.76
		asw3000c01v1ResPatCcFailTrapEnable OBJECT-TYPE
			SYNTAX AlarmEnable
			MAX-ACCESS read-write
			STATUS current
			DESCRIPTION
				"Main PAT continuity counter status Trap Enable"
		::= { asw3000c01v1Entry 76 }

		-- 1.3.6.1.4.1.10106.3.101291.1.1.77
		asw3000c01v1ResTraffFail OBJECT-TYPE
			SYNTAX BitFail
			MAX-ACCESS read-only
			STATUS current
			DESCRIPTION
				"Main bitrate status"
		::= { asw3000c01v1Entry 77 }

		-- 1.3.6.1.4.1.10106.3.101291.1.1.78
		asw3000c01v1ResTraffFailTrapEnable OBJECT-TYPE
			SYNTAX AlarmEnable
			MAX-ACCESS read-write
			STATUS current
			DESCRIPTION
				"Main bitrate status Trap Enable"
		::= { asw3000c01v1Entry 78 }

		-- 1.3.6.1.4.1.10106.3.101291.1.1.79
		asw3000c01v1ResNullPFail OBJECT-TYPE
			SYNTAX BitFail
			MAX-ACCESS read-only
			STATUS current
			DESCRIPTION
				"Main null packet rate status"
		::= { asw3000c01v1Entry 79 }

		-- 1.3.6.1.4.1.10106.3.101291.1.1.80
		asw3000c01v1ResNullPFailTrapEnable OBJECT-TYPE
			SYNTAX AlarmEnable
			MAX-ACCESS read-write
			STATUS current
			DESCRIPTION
				"Main null packet rate status Trap Enable"
		::= { asw3000c01v1Entry 80 }

		-- 1.3.6.1.4.1.10106.3.101291.1.1.81
		asw3000c01v1MainBitrate OBJECT-TYPE
			SYNTAX Bitrate2kbps
			MAX-ACCESS read-only
			STATUS current
			DESCRIPTION
				"Main bitrate"
		::= { asw3000c01v1Entry 81 }

		-- 1.3.6.1.4.1.10106.3.101291.1.1.83
		asw3000c01v1ResBitrate OBJECT-TYPE
			SYNTAX Bitrate2kbps
			MAX-ACCESS read-only
			STATUS current
			DESCRIPTION
				"Reserve bitrate"
		::= { asw3000c01v1Entry 83 }

		-- 1.3.6.1.4.1.10106.3.101291.1.1.85
		asw3000c01v1MainPckNull OBJECT-TYPE
			SYNTAX PckNullRate1
			MAX-ACCESS read-only
			STATUS current
			DESCRIPTION
				"Packet null ratio main"
		::= { asw3000c01v1Entry 85 }

		-- 1.3.6.1.4.1.10106.3.101291.1.1.87
		asw3000c01v1ResPckNull OBJECT-TYPE
			SYNTAX PckNullRate1
			MAX-ACCESS read-only
			STATUS current
			DESCRIPTION
				"Packet null ratio reserve"
		::= { asw3000c01v1Entry 87 }

		-- 1.3.6.1.4.1.10106.3.101291.1.1.89
		asw3000c01v1SerialNo OBJECT-TYPE
			SYNTAX SerialNo
			MAX-ACCESS read-only
			STATUS current
			DESCRIPTION
				"Serial number"
		::= { asw3000c01v1Entry 89 }

		-- 1.3.6.1.4.1.10106.3.245601
		adl3000c01v1 OBJECT IDENTIFIER ::= { albalaProducts 245601 }

		-- 1.3.6.1.4.1.10106.3.245601.1
		adl3000c01v1Table  OBJECT-TYPE
			SYNTAX SEQUENCE OF Adl3000c01v1Entry
			MAX-ACCESS not-accessible
			STATUS current
			DESCRIPTION
				"Module  ADL3000C01V1 Table"
			::= { adl3000c01v1 1 }

		-- 1.3.6.1.4.1.10106.3.245601.1.1
		adl3000c01v1Entry  OBJECT-TYPE
			SYNTAX Adl3000c01v1Entry
			MAX-ACCESS not-accessible
			STATUS current
			DESCRIPTION
				"Module ADL3000C01V1 Entry"
			INDEX { adl3000c01v1Index }
			::= { adl3000c01v1Table 1 }

			Adl3000c01v1Entry ::=
			SEQUENCE {
				adl3000c01v1Index
				ModuleIndex,
				adl3000c01v1OutPckMode
				Bit0Pck1Brs,
				adl3000c01v1OutPckBytes
				Bit02041188,
				adl3000c01v1Delay
				DelayX18Ns,
				adl3000c01v1InPckBytes
				Bit02041188,
				adl3000c01v1NoSig
				BitFail,
				adl3000c01v1NoSync
				BitFail,
				adl3000c01v1BadPckRate
				BitFail,
				adl3000c01v1Unlock
				BitFail,
				adl3000c01v1GlobalFail
				BitFail,
				adl3000c01v1GlobalFailTrapEnable
				AlarmEnable,
				adl3000c01v1Bitrate
				Bitrate2kbps,
				adl3000c01v1DelayOverflow
				Bit0No1Yes,
				adl3000c01v1SerialNo
				SerialNo
			 }

		-- 1.3.6.1.4.1.10106.3.101291.1.1.1
		adl3000c01v1Index OBJECT-TYPE
			SYNTAX ModuleIndex
			MAX-ACCESS read-only
			STATUS current
			DESCRIPTION
				"Index of ADL3000C01V1 Table"
		::= { adl3000c01v1Entry 1 }

		-- 1.3.6.1.4.1.10106.3.101291.1.1.3
		adl3000c01v1OutPckMode OBJECT-TYPE
			SYNTAX Bit0Pck1Brs
			MAX-ACCESS read-write
			STATUS current
			DESCRIPTION
				"Allows selecting the output transmission format"
		::= { adl3000c01v1Entry 3 }

		-- 1.3.6.1.4.1.10106.3.101291.1.1.5
		adl3000c01v1OutPckBytes OBJECT-TYPE
			SYNTAX Bit02041188
			MAX-ACCESS read-write
			STATUS current
			DESCRIPTION
				"Allows selecting the number of bytes in packets in output signal"
		::= { adl3000c01v1Entry 5 }

		-- 1.3.6.1.4.1.10106.3.101291.1.1.7
		adl3000c01v1Delay OBJECT-TYPE
			SYNTAX DelayX18Ns
			MAX-ACCESS read-write
			STATUS current
			DESCRIPTION
				"Allows adjusting the input to output delay"
		::= { adl3000c01v1Entry 7 }

		-- 1.3.6.1.4.1.10106.3.101291.1.1.9
		adl3000c01v1InPckBytes OBJECT-TYPE
			SYNTAX Bit02041188
			MAX-ACCESS read-only
			STATUS current
			DESCRIPTION
				"Indicates the number of bytes in packets in input signal"
		::= { adl3000c01v1Entry 9 }

		-- 1.3.6.1.4.1.10106.3.101291.1.1.11
		adl3000c01v1NoSig OBJECT-TYPE
			SYNTAX BitFail
			MAX-ACCESS read-only
			STATUS current
			DESCRIPTION
				"Input signal status"
		::= { adl3000c01v1Entry 11 }

		-- 1.3.6.1.4.1.10106.3.101291.1.1.13
		adl3000c01v1NoSync OBJECT-TYPE
			SYNTAX BitFail
			MAX-ACCESS read-only
			STATUS current
			DESCRIPTION
				"Indicates TS sync loss"
		::= { adl3000c01v1Entry 13 }

		-- 1.3.6.1.4.1.10106.3.101291.1.1.15
		adl3000c01v1BadPckRate OBJECT-TYPE
			SYNTAX BitFail
			MAX-ACCESS read-only
			STATUS current
			DESCRIPTION
				"Indicates a bad packet rate"
		::= { adl3000c01v1Entry 15 }

		-- 1.3.6.1.4.1.10106.3.101291.1.1.17
		adl3000c01v1Unlock OBJECT-TYPE
			SYNTAX BitFail
			MAX-ACCESS read-only
			STATUS current
			DESCRIPTION
				"Indicates signal unlock fail"
		::= { adl3000c01v1Entry 17 }

		-- 1.3.6.1.4.1.10106.3.101291.1.1.19
		adl3000c01v1GlobalFail OBJECT-TYPE
			SYNTAX BitFail
			MAX-ACCESS read-only
			STATUS current
			DESCRIPTION
				"Input global (any kind) fail status"
		::= { adl3000c01v1Entry 19 }

		-- 1.3.6.1.4.1.10106.3.101291.1.1.20
		adl3000c01v1GlobalFailTrapEnable OBJECT-TYPE
			SYNTAX AlarmEnable
			MAX-ACCESS read-write
			STATUS current
			DESCRIPTION
				"Input global (any kind) fail status Trap Enable"
		::= { adl3000c01v1Entry 20 }

		-- 1.3.6.1.4.1.10106.3.101291.1.1.21
		adl3000c01v1Bitrate OBJECT-TYPE
			SYNTAX Bitrate2kbps
			MAX-ACCESS read-only
			STATUS current
			DESCRIPTION
				"Bitrate"
		::= { adl3000c01v1Entry 21 }

		-- 1.3.6.1.4.1.10106.3.101291.1.1.23
		adl3000c01v1DelayOverflow OBJECT-TYPE
			SYNTAX Bit0No1Yes
			MAX-ACCESS read-only
			STATUS current
			DESCRIPTION
				"Indicates a programmed delay overflow"
		::= { adl3000c01v1Entry 23 }

		-- 1.3.6.1.4.1.10106.3.101291.1.1.25
		adl3000c01v1SerialNo OBJECT-TYPE
			SYNTAX SerialNo
			MAX-ACCESS read-only
			STATUS current
			DESCRIPTION
				"Serial number"
		::= { adl3000c01v1Entry 25 }

		-- 1.3.6.1.4.1.10106.3.247001
		hvd3000c01v1 OBJECT IDENTIFIER ::= { albalaProducts 247001 }

		-- 1.3.6.1.4.1.10106.3.247001.1
		hvd3000c01v1Table  OBJECT-TYPE
			SYNTAX SEQUENCE OF Hvd3000c01v1Entry
			MAX-ACCESS not-accessible
			STATUS current
			DESCRIPTION
				"Module  HVD3000C01V1 Table"
			::= { hvd3000c01v1 1 }

		-- 1.3.6.1.4.1.10106.3.247001.1.1
		hvd3000c01v1Entry  OBJECT-TYPE
			SYNTAX Hvd3000c01v1Entry
			MAX-ACCESS not-accessible
			STATUS current
			DESCRIPTION
				"Module HVD3000C01V1 Entry"
			INDEX { hvd3000c01v1Index }
			::= { hvd3000c01v1Table 1 }

			Hvd3000c01v1Entry ::=
			SEQUENCE {
				hvd3000c01v1Index
				ModuleIndex,
				hvd3000c01v1DvdMode
				BitDistrib1,
				hvd3000c01v1NoSigA
				BitFail,
				hvd3000c01v1NoSigATrapEnable
				AlarmEnable,
				hvd3000c01v1MaxEqA
				BitFail,
				hvd3000c01v1UnlockA
				BitFail,
				hvd3000c01v1UnlockATrapEnable
				AlarmEnable,
				hvd3000c01v1NoSigB
				BitFail,
				hvd3000c01v1NoSigBTrapEnable
				AlarmEnable,
				hvd3000c01v1MaxEqB
				BitFail,
				hvd3000c01v1UnlockB
				BitFail,
				hvd3000c01v1UnlockBTrapEnable
				AlarmEnable,
				hvd3000c01v1CableLengthA
				Rate1,
				hvd3000c01v1CableLengthB
				Rate1,
				hvd3000c01v1SerialNo
				SerialNo
			 }

		-- 1.3.6.1.4.1.10106.3.101291.1.1.1
		hvd3000c01v1Index OBJECT-TYPE
			SYNTAX ModuleIndex
			MAX-ACCESS read-only
			STATUS current
			DESCRIPTION
				"Index of HVD3000C01V1 Table"
		::= { hvd3000c01v1Entry 1 }

		-- 1.3.6.1.4.1.10106.3.101291.1.1.3
		hvd3000c01v1DvdMode OBJECT-TYPE
			SYNTAX BitDistrib1
			MAX-ACCESS read-write
			STATUS current
			DESCRIPTION
				"Operating mode"
		::= { hvd3000c01v1Entry 3 }

		-- 1.3.6.1.4.1.10106.3.101291.1.1.5
		hvd3000c01v1NoSigA OBJECT-TYPE
			SYNTAX BitFail
			MAX-ACCESS read-only
			STATUS current
			DESCRIPTION
				"Input signal status"
		::= { hvd3000c01v1Entry 5 }

		-- 1.3.6.1.4.1.10106.3.101291.1.1.6
		hvd3000c01v1NoSigATrapEnable OBJECT-TYPE
			SYNTAX AlarmEnable
			MAX-ACCESS read-write
			STATUS current
			DESCRIPTION
				"Input signal status Trap Enable"
		::= { hvd3000c01v1Entry 6 }

		-- 1.3.6.1.4.1.10106.3.101291.1.1.7
		hvd3000c01v1MaxEqA OBJECT-TYPE
			SYNTAX BitFail
			MAX-ACCESS read-only
			STATUS current
			DESCRIPTION
				"Indicates maximum equalization"
		::= { hvd3000c01v1Entry 7 }

		-- 1.3.6.1.4.1.10106.3.101291.1.1.9
		hvd3000c01v1UnlockA OBJECT-TYPE
			SYNTAX BitFail
			MAX-ACCESS read-only
			STATUS current
			DESCRIPTION
				"Indicates signal unlock fail"
		::= { hvd3000c01v1Entry 9 }

		-- 1.3.6.1.4.1.10106.3.101291.1.1.10
		hvd3000c01v1UnlockATrapEnable OBJECT-TYPE
			SYNTAX AlarmEnable
			MAX-ACCESS read-write
			STATUS current
			DESCRIPTION
				"Indicates signal unlock fail Trap Enable"
		::= { hvd3000c01v1Entry 10 }

		-- 1.3.6.1.4.1.10106.3.101291.1.1.11
		hvd3000c01v1NoSigB OBJECT-TYPE
			SYNTAX BitFail
			MAX-ACCESS read-only
			STATUS current
			DESCRIPTION
				"Input signal status"
		::= { hvd3000c01v1Entry 11 }

		-- 1.3.6.1.4.1.10106.3.101291.1.1.12
		hvd3000c01v1NoSigBTrapEnable OBJECT-TYPE
			SYNTAX AlarmEnable
			MAX-ACCESS read-write
			STATUS current
			DESCRIPTION
				"Input signal status Trap Enable"
		::= { hvd3000c01v1Entry 12 }

		-- 1.3.6.1.4.1.10106.3.101291.1.1.13
		hvd3000c01v1MaxEqB OBJECT-TYPE
			SYNTAX BitFail
			MAX-ACCESS read-only
			STATUS current
			DESCRIPTION
				"Indicates maximum equalization"
		::= { hvd3000c01v1Entry 13 }

		-- 1.3.6.1.4.1.10106.3.101291.1.1.15
		hvd3000c01v1UnlockB OBJECT-TYPE
			SYNTAX BitFail
			MAX-ACCESS read-only
			STATUS current
			DESCRIPTION
				"Indicates signal unlock fail"
		::= { hvd3000c01v1Entry 15 }

		-- 1.3.6.1.4.1.10106.3.101291.1.1.16
		hvd3000c01v1UnlockBTrapEnable OBJECT-TYPE
			SYNTAX AlarmEnable
			MAX-ACCESS read-write
			STATUS current
			DESCRIPTION
				"Indicates signal unlock fail Trap Enable"
		::= { hvd3000c01v1Entry 16 }

		-- 1.3.6.1.4.1.10106.3.101291.1.1.17
		hvd3000c01v1CableLengthA OBJECT-TYPE
			SYNTAX Rate1
			MAX-ACCESS read-only
			STATUS current
			DESCRIPTION
				"Equalization level refered to maximun"
		::= { hvd3000c01v1Entry 17 }

		-- 1.3.6.1.4.1.10106.3.101291.1.1.19
		hvd3000c01v1CableLengthB OBJECT-TYPE
			SYNTAX Rate1
			MAX-ACCESS read-only
			STATUS current
			DESCRIPTION
				"Equalization level refered to maximun"
		::= { hvd3000c01v1Entry 19 }

		-- 1.3.6.1.4.1.10106.3.101291.1.1.21
		hvd3000c01v1SerialNo OBJECT-TYPE
			SYNTAX SerialNo
			MAX-ACCESS read-only
			STATUS current
			DESCRIPTION
				"Serial number"
		::= { hvd3000c01v1Entry 21 }

		-- 1.3.6.1.4.1.10106.3.247002
		hvd3000c01v2 OBJECT IDENTIFIER ::= { albalaProducts 247002 }

		-- 1.3.6.1.4.1.10106.3.247002.1
		hvd3000c01v2Table  OBJECT-TYPE
			SYNTAX SEQUENCE OF Hvd3000c01v2Entry
			MAX-ACCESS not-accessible
			STATUS current
			DESCRIPTION
				"Module  HVD3000C01V2 Table"
			::= { hvd3000c01v2 1 }

		-- 1.3.6.1.4.1.10106.3.247002.1.1
		hvd3000c01v2Entry  OBJECT-TYPE
			SYNTAX Hvd3000c01v2Entry
			MAX-ACCESS not-accessible
			STATUS current
			DESCRIPTION
				"Module HVD3000C01V2 Entry"
			INDEX { hvd3000c01v2Index }
			::= { hvd3000c01v2Table 1 }

			Hvd3000c01v2Entry ::=
			SEQUENCE {
				hvd3000c01v2Index
				ModuleIndex,
				hvd3000c01v2DvdMode
				BitDistrib1,
				hvd3000c01v2NoSigA
				BitFail,
				hvd3000c01v2NoSigATrapEnable
				AlarmEnable,
				hvd3000c01v2UnlockA
				BitFail,
				hvd3000c01v2UnlockATrapEnable
				AlarmEnable,
				hvd3000c01v2NoSigB
				BitFail,
				hvd3000c01v2NoSigBTrapEnable
				AlarmEnable,
				hvd3000c01v2UnlockB
				BitFail,
				hvd3000c01v2UnlockBTrapEnable
				AlarmEnable,
				hvd3000c01v2SerialNo
				SerialNo
			 }

		-- 1.3.6.1.4.1.10106.3.101291.1.1.1
		hvd3000c01v2Index OBJECT-TYPE
			SYNTAX ModuleIndex
			MAX-ACCESS read-only
			STATUS current
			DESCRIPTION
				"Index of HVD3000C01V2 Table"
		::= { hvd3000c01v2Entry 1 }

		-- 1.3.6.1.4.1.10106.3.101291.1.1.3
		hvd3000c01v2DvdMode OBJECT-TYPE
			SYNTAX BitDistrib1
			MAX-ACCESS read-write
			STATUS current
			DESCRIPTION
				"Operating mode"
		::= { hvd3000c01v2Entry 3 }

		-- 1.3.6.1.4.1.10106.3.101291.1.1.5
		hvd3000c01v2NoSigA OBJECT-TYPE
			SYNTAX BitFail
			MAX-ACCESS read-only
			STATUS current
			DESCRIPTION
				"Input signal status"
		::= { hvd3000c01v2Entry 5 }

		-- 1.3.6.1.4.1.10106.3.101291.1.1.6
		hvd3000c01v2NoSigATrapEnable OBJECT-TYPE
			SYNTAX AlarmEnable
			MAX-ACCESS read-write
			STATUS current
			DESCRIPTION
				"Input signal status Trap Enable"
		::= { hvd3000c01v2Entry 6 }

		-- 1.3.6.1.4.1.10106.3.101291.1.1.7
		hvd3000c01v2UnlockA OBJECT-TYPE
			SYNTAX BitFail
			MAX-ACCESS read-only
			STATUS current
			DESCRIPTION
				"Indicates signal unlock fail"
		::= { hvd3000c01v2Entry 7 }

		-- 1.3.6.1.4.1.10106.3.101291.1.1.8
		hvd3000c01v2UnlockATrapEnable OBJECT-TYPE
			SYNTAX AlarmEnable
			MAX-ACCESS read-write
			STATUS current
			DESCRIPTION
				"Indicates signal unlock fail Trap Enable"
		::= { hvd3000c01v2Entry 8 }

		-- 1.3.6.1.4.1.10106.3.101291.1.1.9
		hvd3000c01v2NoSigB OBJECT-TYPE
			SYNTAX BitFail
			MAX-ACCESS read-only
			STATUS current
			DESCRIPTION
				"Input signal status"
		::= { hvd3000c01v2Entry 9 }

		-- 1.3.6.1.4.1.10106.3.101291.1.1.10
		hvd3000c01v2NoSigBTrapEnable OBJECT-TYPE
			SYNTAX AlarmEnable
			MAX-ACCESS read-write
			STATUS current
			DESCRIPTION
				"Input signal status Trap Enable"
		::= { hvd3000c01v2Entry 10 }

		-- 1.3.6.1.4.1.10106.3.101291.1.1.11
		hvd3000c01v2UnlockB OBJECT-TYPE
			SYNTAX BitFail
			MAX-ACCESS read-only
			STATUS current
			DESCRIPTION
				"Indicates signal unlock fail"
		::= { hvd3000c01v2Entry 11 }

		-- 1.3.6.1.4.1.10106.3.101291.1.1.12
		hvd3000c01v2UnlockBTrapEnable OBJECT-TYPE
			SYNTAX AlarmEnable
			MAX-ACCESS read-write
			STATUS current
			DESCRIPTION
				"Indicates signal unlock fail Trap Enable"
		::= { hvd3000c01v2Entry 12 }

		-- 1.3.6.1.4.1.10106.3.101291.1.1.13
		hvd3000c01v2SerialNo OBJECT-TYPE
			SYNTAX SerialNo
			MAX-ACCESS read-only
			STATUS current
			DESCRIPTION
				"Serial number"
		::= { hvd3000c01v2Entry 13 }

		-- 1.3.6.1.4.1.10106.3.247101
		hdt3000c01v1 OBJECT IDENTIFIER ::= { albalaProducts 247101 }

		-- 1.3.6.1.4.1.10106.3.247101.1
		hdt3000c01v1Table  OBJECT-TYPE
			SYNTAX SEQUENCE OF Hdt3000c01v1Entry
			MAX-ACCESS not-accessible
			STATUS current
			DESCRIPTION
				"Module  HDT3000C01V1 Table"
			::= { hdt3000c01v1 1 }

		-- 1.3.6.1.4.1.10106.3.247101.1.1
		hdt3000c01v1Entry  OBJECT-TYPE
			SYNTAX Hdt3000c01v1Entry
			MAX-ACCESS not-accessible
			STATUS current
			DESCRIPTION
				"Module HDT3000C01V1 Entry"
			INDEX { hdt3000c01v1Index }
			::= { hdt3000c01v1Table 1 }

			Hdt3000c01v1Entry ::=
			SEQUENCE {
				hdt3000c01v1Index
				ModuleIndex,
				hdt3000c01v1NoSigA
				BitFail,
				hdt3000c01v1NoSigATrapEnable
				AlarmEnable,
				hdt3000c01v1UnlockA
				BitFail,
				hdt3000c01v1UnlockATrapEnable
				AlarmEnable,
				hdt3000c01v1LaserFailA
				BitFail,
				hdt3000c01v1LaserFailATrapEnable
				AlarmEnable,
				hdt3000c01v1SdiFormatA
				Bit0Hd1Sd,
				hdt3000c01v1NoSigB
				BitFail,
				hdt3000c01v1NoSigBTrapEnable
				AlarmEnable,
				hdt3000c01v1UnlockB
				BitFail,
				hdt3000c01v1UnlockBTrapEnable
				AlarmEnable,
				hdt3000c01v1LaserFailB
				BitFail,
				hdt3000c01v1LaserFailBTrapEnable
				AlarmEnable,
				hdt3000c01v1SdiFormatB
				Bit0Hd1Sd,
				hdt3000c01v1SerialNo
				SerialNo
			 }

		-- 1.3.6.1.4.1.10106.3.101291.1.1.1
		hdt3000c01v1Index OBJECT-TYPE
			SYNTAX ModuleIndex
			MAX-ACCESS read-only
			STATUS current
			DESCRIPTION
				"Index of HDT3000C01V1 Table"
		::= { hdt3000c01v1Entry 1 }

		-- 1.3.6.1.4.1.10106.3.101291.1.1.3
		hdt3000c01v1NoSigA OBJECT-TYPE
			SYNTAX BitFail
			MAX-ACCESS read-only
			STATUS current
			DESCRIPTION
				"Input signal status"
		::= { hdt3000c01v1Entry 3 }

		-- 1.3.6.1.4.1.10106.3.101291.1.1.4
		hdt3000c01v1NoSigATrapEnable OBJECT-TYPE
			SYNTAX AlarmEnable
			MAX-ACCESS read-write
			STATUS current
			DESCRIPTION
				"Input signal status Trap Enable"
		::= { hdt3000c01v1Entry 4 }

		-- 1.3.6.1.4.1.10106.3.101291.1.1.5
		hdt3000c01v1UnlockA OBJECT-TYPE
			SYNTAX BitFail
			MAX-ACCESS read-only
			STATUS current
			DESCRIPTION
				"Indicates signal unlock fail"
		::= { hdt3000c01v1Entry 5 }

		-- 1.3.6.1.4.1.10106.3.101291.1.1.6
		hdt3000c01v1UnlockATrapEnable OBJECT-TYPE
			SYNTAX AlarmEnable
			MAX-ACCESS read-write
			STATUS current
			DESCRIPTION
				"Indicates signal unlock fail Trap Enable"
		::= { hdt3000c01v1Entry 6 }

		-- 1.3.6.1.4.1.10106.3.101291.1.1.7
		hdt3000c01v1LaserFailA OBJECT-TYPE
			SYNTAX BitFail
			MAX-ACCESS read-only
			STATUS current
			DESCRIPTION
				"Laser status"
		::= { hdt3000c01v1Entry 7 }

		-- 1.3.6.1.4.1.10106.3.101291.1.1.8
		hdt3000c01v1LaserFailATrapEnable OBJECT-TYPE
			SYNTAX AlarmEnable
			MAX-ACCESS read-write
			STATUS current
			DESCRIPTION
				"Laser status Trap Enable"
		::= { hdt3000c01v1Entry 8 }

		-- 1.3.6.1.4.1.10106.3.101291.1.1.9
		hdt3000c01v1SdiFormatA OBJECT-TYPE
			SYNTAX Bit0Hd1Sd
			MAX-ACCESS read-only
			STATUS current
			DESCRIPTION
				"Indicates de SDI format"
		::= { hdt3000c01v1Entry 9 }

		-- 1.3.6.1.4.1.10106.3.101291.1.1.11
		hdt3000c01v1NoSigB OBJECT-TYPE
			SYNTAX BitFail
			MAX-ACCESS read-only
			STATUS current
			DESCRIPTION
				"Input signal status"
		::= { hdt3000c01v1Entry 11 }

		-- 1.3.6.1.4.1.10106.3.101291.1.1.12
		hdt3000c01v1NoSigBTrapEnable OBJECT-TYPE
			SYNTAX AlarmEnable
			MAX-ACCESS read-write
			STATUS current
			DESCRIPTION
				"Input signal status Trap Enable"
		::= { hdt3000c01v1Entry 12 }

		-- 1.3.6.1.4.1.10106.3.101291.1.1.13
		hdt3000c01v1UnlockB OBJECT-TYPE
			SYNTAX BitFail
			MAX-ACCESS read-only
			STATUS current
			DESCRIPTION
				"Indicates signal unlock fail"
		::= { hdt3000c01v1Entry 13 }

		-- 1.3.6.1.4.1.10106.3.101291.1.1.14
		hdt3000c01v1UnlockBTrapEnable OBJECT-TYPE
			SYNTAX AlarmEnable
			MAX-ACCESS read-write
			STATUS current
			DESCRIPTION
				"Indicates signal unlock fail Trap Enable"
		::= { hdt3000c01v1Entry 14 }

		-- 1.3.6.1.4.1.10106.3.101291.1.1.15
		hdt3000c01v1LaserFailB OBJECT-TYPE
			SYNTAX BitFail
			MAX-ACCESS read-only
			STATUS current
			DESCRIPTION
				"Laser status"
		::= { hdt3000c01v1Entry 15 }

		-- 1.3.6.1.4.1.10106.3.101291.1.1.16
		hdt3000c01v1LaserFailBTrapEnable OBJECT-TYPE
			SYNTAX AlarmEnable
			MAX-ACCESS read-write
			STATUS current
			DESCRIPTION
				"Laser status Trap Enable"
		::= { hdt3000c01v1Entry 16 }

		-- 1.3.6.1.4.1.10106.3.101291.1.1.17
		hdt3000c01v1SdiFormatB OBJECT-TYPE
			SYNTAX Bit0Hd1Sd
			MAX-ACCESS read-only
			STATUS current
			DESCRIPTION
				"Indicates de SDI format"
		::= { hdt3000c01v1Entry 17 }

		-- 1.3.6.1.4.1.10106.3.101291.1.1.19
		hdt3000c01v1SerialNo OBJECT-TYPE
			SYNTAX SerialNo
			MAX-ACCESS read-only
			STATUS current
			DESCRIPTION
				"Serial number"
		::= { hdt3000c01v1Entry 19 }

		-- 1.3.6.1.4.1.10106.3.247201
		hdr3000c01v1 OBJECT IDENTIFIER ::= { albalaProducts 247201 }

		-- 1.3.6.1.4.1.10106.3.247201.1
		hdr3000c01v1Table  OBJECT-TYPE
			SYNTAX SEQUENCE OF Hdr3000c01v1Entry
			MAX-ACCESS not-accessible
			STATUS current
			DESCRIPTION
				"Module  HDR3000C01V1 Table"
			::= { hdr3000c01v1 1 }

		-- 1.3.6.1.4.1.10106.3.247201.1.1
		hdr3000c01v1Entry  OBJECT-TYPE
			SYNTAX Hdr3000c01v1Entry
			MAX-ACCESS not-accessible
			STATUS current
			DESCRIPTION
				"Module HDR3000C01V1 Entry"
			INDEX { hdr3000c01v1Index }
			::= { hdr3000c01v1Table 1 }

			Hdr3000c01v1Entry ::=
			SEQUENCE {
				hdr3000c01v1Index
				ModuleIndex,
				hdr3000c01v1InputSelA
				Bit0Opt1Ele,
				hdr3000c01v1InputSelB
				Bit0Opt1Ele,
				hdr3000c01v1NoSigEA
				BitFail,
				hdr3000c01v1NoSigEATrapEnable
				AlarmEnable,
				hdr3000c01v1LowPowerA
				BitFail,
				hdr3000c01v1NoSigEOA
				BitFail,
				hdr3000c01v1NoSigEOATrapEnable
				AlarmEnable,
				hdr3000c01v1UnlockA
				BitFail,
				hdr3000c01v1UnlockATrapEnable
				AlarmEnable,
				hdr3000c01v1SdiFormatA
				Bit0Hd1Sd,
				hdr3000c01v1NoSigEB
				BitFail,
				hdr3000c01v1NoSigEBTrapEnable
				AlarmEnable,
				hdr3000c01v1LowPowerB
				BitFail,
				hdr3000c01v1NoSigOB
				BitFail,
				hdr3000c01v1NoSigOBTrapEnable
				AlarmEnable,
				hdr3000c01v1UnlockB
				BitFail,
				hdr3000c01v1UnlockBTrapEnable
				AlarmEnable,
				hdr3000c01v1SdiFormatB
				Bit0Hd1Sd,
				hdr3000c01v1SerialNo
				SerialNo
			 }

		-- 1.3.6.1.4.1.10106.3.101291.1.1.1
		hdr3000c01v1Index OBJECT-TYPE
			SYNTAX ModuleIndex
			MAX-ACCESS read-only
			STATUS current
			DESCRIPTION
				"Index of HDR3000C01V1 Table"
		::= { hdr3000c01v1Entry 1 }

		-- 1.3.6.1.4.1.10106.3.101291.1.1.3
		hdr3000c01v1InputSelA OBJECT-TYPE
			SYNTAX Bit0Opt1Ele
			MAX-ACCESS read-write
			STATUS current
			DESCRIPTION
				"Allows selecting the active input"
		::= { hdr3000c01v1Entry 3 }

		-- 1.3.6.1.4.1.10106.3.101291.1.1.5
		hdr3000c01v1InputSelB OBJECT-TYPE
			SYNTAX Bit0Opt1Ele
			MAX-ACCESS read-write
			STATUS current
			DESCRIPTION
				"Allows selecting the active input"
		::= { hdr3000c01v1Entry 5 }

		-- 1.3.6.1.4.1.10106.3.101291.1.1.7
		hdr3000c01v1NoSigEA OBJECT-TYPE
			SYNTAX BitFail
			MAX-ACCESS read-only
			STATUS current
			DESCRIPTION
				"Electrical input signal status"
		::= { hdr3000c01v1Entry 7 }

		-- 1.3.6.1.4.1.10106.3.101291.1.1.8
		hdr3000c01v1NoSigEATrapEnable OBJECT-TYPE
			SYNTAX AlarmEnable
			MAX-ACCESS read-write
			STATUS current
			DESCRIPTION
				"Electrical input signal status Trap Enable"
		::= { hdr3000c01v1Entry 8 }

		-- 1.3.6.1.4.1.10106.3.101291.1.1.9
		hdr3000c01v1LowPowerA OBJECT-TYPE
			SYNTAX BitFail
			MAX-ACCESS read-only
			STATUS current
			DESCRIPTION
				"Indicates low optical power"
		::= { hdr3000c01v1Entry 9 }

		-- 1.3.6.1.4.1.10106.3.101291.1.1.11
		hdr3000c01v1NoSigEOA OBJECT-TYPE
			SYNTAX BitFail
			MAX-ACCESS read-only
			STATUS current
			DESCRIPTION
				"Optical input signal status"
		::= { hdr3000c01v1Entry 11 }

		-- 1.3.6.1.4.1.10106.3.101291.1.1.12
		hdr3000c01v1NoSigEOATrapEnable OBJECT-TYPE
			SYNTAX AlarmEnable
			MAX-ACCESS read-write
			STATUS current
			DESCRIPTION
				"Optical input signal status Trap Enable"
		::= { hdr3000c01v1Entry 12 }

		-- 1.3.6.1.4.1.10106.3.101291.1.1.13
		hdr3000c01v1UnlockA OBJECT-TYPE
			SYNTAX BitFail
			MAX-ACCESS read-only
			STATUS current
			DESCRIPTION
				"Indicates signal unlock fail"
		::= { hdr3000c01v1Entry 13 }

		-- 1.3.6.1.4.1.10106.3.101291.1.1.14
		hdr3000c01v1UnlockATrapEnable OBJECT-TYPE
			SYNTAX AlarmEnable
			MAX-ACCESS read-write
			STATUS current
			DESCRIPTION
				"Indicates signal unlock fail Trap Enable"
		::= { hdr3000c01v1Entry 14 }

		-- 1.3.6.1.4.1.10106.3.101291.1.1.15
		hdr3000c01v1SdiFormatA OBJECT-TYPE
			SYNTAX Bit0Hd1Sd
			MAX-ACCESS read-only
			STATUS current
			DESCRIPTION
				"Indicates de SDI format"
		::= { hdr3000c01v1Entry 15 }

		-- 1.3.6.1.4.1.10106.3.101291.1.1.17
		hdr3000c01v1NoSigEB OBJECT-TYPE
			SYNTAX BitFail
			MAX-ACCESS read-only
			STATUS current
			DESCRIPTION
				"Electrical input signal status"
		::= { hdr3000c01v1Entry 17 }

		-- 1.3.6.1.4.1.10106.3.101291.1.1.18
		hdr3000c01v1NoSigEBTrapEnable OBJECT-TYPE
			SYNTAX AlarmEnable
			MAX-ACCESS read-write
			STATUS current
			DESCRIPTION
				"Electrical input signal status Trap Enable"
		::= { hdr3000c01v1Entry 18 }

		-- 1.3.6.1.4.1.10106.3.101291.1.1.19
		hdr3000c01v1LowPowerB OBJECT-TYPE
			SYNTAX BitFail
			MAX-ACCESS read-only
			STATUS current
			DESCRIPTION
				"Indicates low optical power"
		::= { hdr3000c01v1Entry 19 }

		-- 1.3.6.1.4.1.10106.3.101291.1.1.21
		hdr3000c01v1NoSigOB OBJECT-TYPE
			SYNTAX BitFail
			MAX-ACCESS read-only
			STATUS current
			DESCRIPTION
				"Optical input signal status"
		::= { hdr3000c01v1Entry 21 }

		-- 1.3.6.1.4.1.10106.3.101291.1.1.22
		hdr3000c01v1NoSigOBTrapEnable OBJECT-TYPE
			SYNTAX AlarmEnable
			MAX-ACCESS read-write
			STATUS current
			DESCRIPTION
				"Optical input signal status Trap Enable"
		::= { hdr3000c01v1Entry 22 }

		-- 1.3.6.1.4.1.10106.3.101291.1.1.23
		hdr3000c01v1UnlockB OBJECT-TYPE
			SYNTAX BitFail
			MAX-ACCESS read-only
			STATUS current
			DESCRIPTION
				"Indicates signal unlock fail"
		::= { hdr3000c01v1Entry 23 }

		-- 1.3.6.1.4.1.10106.3.101291.1.1.24
		hdr3000c01v1UnlockBTrapEnable OBJECT-TYPE
			SYNTAX AlarmEnable
			MAX-ACCESS read-write
			STATUS current
			DESCRIPTION
				"Indicates signal unlock fail Trap Enable"
		::= { hdr3000c01v1Entry 24 }

		-- 1.3.6.1.4.1.10106.3.101291.1.1.25
		hdr3000c01v1SdiFormatB OBJECT-TYPE
			SYNTAX Bit0Hd1Sd
			MAX-ACCESS read-only
			STATUS current
			DESCRIPTION
				"Indicates de SDI format"
		::= { hdr3000c01v1Entry 25 }

		-- 1.3.6.1.4.1.10106.3.101291.1.1.27
		hdr3000c01v1SerialNo OBJECT-TYPE
			SYNTAX SerialNo
			MAX-ACCESS read-only
			STATUS current
			DESCRIPTION
				"Serial number"
		::= { hdr3000c01v1Entry 27 }

		-- 1.3.6.1.4.1.10106.3.259501
		dli3001c01v1 OBJECT IDENTIFIER ::= { albalaProducts 259501 }

		-- 1.3.6.1.4.1.10106.3.259501.1
		dli3001c01v1Table  OBJECT-TYPE
			SYNTAX SEQUENCE OF Dli3001c01v1Entry
			MAX-ACCESS not-accessible
			STATUS current
			DESCRIPTION
				"Module  DLI3001C01V1 Table"
			::= { dli3001c01v1 1 }

		-- 1.3.6.1.4.1.10106.3.259501.1.1
		dli3001c01v1Entry  OBJECT-TYPE
			SYNTAX Dli3001c01v1Entry
			MAX-ACCESS not-accessible
			STATUS current
			DESCRIPTION
				"Module DLI3001C01V1 Entry"
			INDEX { dli3001c01v1Index }
			::= { dli3001c01v1Table 1 }

			Dli3001c01v1Entry ::=
			SEQUENCE {
				dli3001c01v1Index
				ModuleIndex,
				dli3001c01v1ActivePreset
				PresetActive,
				dli3001c01v1LoadPreset
				PresetLoad,
				dli3001c01v1SavePreset
				PresetSave,
				dli3001c01v1PgmInsLogo1
				Bit0No1Yes,
				dli3001c01v1PgmInsLogo2
				Bit0No1Yes,
				dli3001c01v1PgmInsLogo3
				Bit0No1Yes,
				dli3001c01v1PgmInsLogo4
				Bit0No1Yes,
				dli3001c01v1PvwInsLogo1
				Bit0No1Yes,
				dli3001c01v1PvwInsLogo2
				Bit0No1Yes,
				dli3001c01v1PvwInsLogo3
				Bit0No1Yes,
				dli3001c01v1PvwInsLogo4
				Bit0No1Yes,
				dli3001c01v1MixAudio
				Bit0No1Yes,
				dli3001c01v1RestartAudio
				Bit0No1Yes,
				dli3001c01v1SelLogo1
				Uint6,
				dli3001c01v1SelLogo2
				Uint6,
				dli3001c01v1SelLogo3
				Uint6,
				dli3001c01v1SelLogo4
				Uint6,
				dli3001c01v1Group
				EmbedGroup,
				dli3001c01v1InsAudio
				Bit0No1Yes,
				dli3001c01v1EmbedBits
				Bit024120,
				dli3001c01v1CleanAudioGr1
				Bit0No1Yes,
				dli3001c01v1CleanAudioGr2
				Bit0No1Yes,
				dli3001c01v1CleanAudioGr3
				Bit0No1Yes,
				dli3001c01v1CleanAudioGr4
				Bit0No1Yes,
				dli3001c01v1GpiMode
				Bit0Lev1Edg,
				dli3001c01v1LoadLogo
				Bit0No1Yes,
				dli3001c01v1PosHLogo1Msb
				Uint2,
				dli3001c01v1PosHLogo1Lsb
				Uint8,
				dli3001c01v1PosVLogo1Msb
				Uint1,
				dli3001c01v1PosVLogo1Lsb
				Uint8,
				dli3001c01v1PosHLogo2Msb
				Uint2,
				dli3001c01v1PosHLogo2Lsb
				Uint7,
				dli3001c01v1PosVLogo2Msb
				Uint1,
				dli3001c01v1PosVLogo2Lsb
				Uint8,
				dli3001c01v1PosHLogo3Msb
				Uint2,
				dli3001c01v1PosHLogo3Lsb
				Uint7,
				dli3001c01v1PosVLogo3Msb
				Uint1,
				dli3001c01v1PosVLogo3Lsb
				Uint8,
				dli3001c01v1PosHLogo4Msb
				Uint2,
				dli3001c01v1PosHLogo4Lsb
				Uint7,
				dli3001c01v1PosVLogo4Msb
				Uint1,
				dli3001c01v1PosVLogo4Lsb
				Uint8,
				dli3001c01v1NoSig
				BitFail,
				dli3001c01v1NoSigTrapEnable
				AlarmEnable,
				dli3001c01v1EdhErr
				BitFail,
				dli3001c01v1AudioFr0Err
				BitFail,
				dli3001c01v1AudioFr0ErrTrapEnable
				AlarmEnable,
				dli3001c01v1AudioFr1Err
				BitFail,
				dli3001c01v1AudioFr1ErrTrapEnable
				AlarmEnable,
				dli3001c01v1AudioGr1
				Bit0No1Yes,
				dli3001c01v1AudioGr2
				Bit0No1Yes,
				dli3001c01v1AudioGr3
				Bit0No1Yes,
				dli3001c01v1AudioGr4
				Bit0No1Yes
			 }

		-- 1.3.6.1.4.1.10106.3.101291.1.1.1
		dli3001c01v1Index OBJECT-TYPE
			SYNTAX ModuleIndex
			MAX-ACCESS read-only
			STATUS current
			DESCRIPTION
				"Index of DLI3001C01V1 Table"
		::= { dli3001c01v1Entry 1 }

		-- 1.3.6.1.4.1.10106.3.101291.1.1.3
		dli3001c01v1ActivePreset OBJECT-TYPE
			SYNTAX PresetActive
			MAX-ACCESS read-only
			STATUS current
			DESCRIPTION
				"Shows the active preset"
		::= { dli3001c01v1Entry 3 }

		-- 1.3.6.1.4.1.10106.3.101291.1.1.5
		dli3001c01v1LoadPreset OBJECT-TYPE
			SYNTAX PresetLoad
			MAX-ACCESS read-write
			STATUS current
			DESCRIPTION
				"Allows loading a preset"
		::= { dli3001c01v1Entry 5 }

		-- 1.3.6.1.4.1.10106.3.101291.1.1.7
		dli3001c01v1SavePreset OBJECT-TYPE
			SYNTAX PresetSave
			MAX-ACCESS read-write
			STATUS current
			DESCRIPTION
				"Allows saving a preset"
		::= { dli3001c01v1Entry 7 }

		-- 1.3.6.1.4.1.10106.3.101291.1.1.9
		dli3001c01v1PgmInsLogo1 OBJECT-TYPE
			SYNTAX Bit0No1Yes
			MAX-ACCESS read-write
			STATUS current
			DESCRIPTION
				"Allows inserting the logo in the program output"
		::= { dli3001c01v1Entry 9 }

		-- 1.3.6.1.4.1.10106.3.101291.1.1.11
		dli3001c01v1PgmInsLogo2 OBJECT-TYPE
			SYNTAX Bit0No1Yes
			MAX-ACCESS read-write
			STATUS current
			DESCRIPTION
				"Allows inserting the logo in the program output"
		::= { dli3001c01v1Entry 11 }

		-- 1.3.6.1.4.1.10106.3.101291.1.1.13
		dli3001c01v1PgmInsLogo3 OBJECT-TYPE
			SYNTAX Bit0No1Yes
			MAX-ACCESS read-write
			STATUS current
			DESCRIPTION
				"Allows inserting the logo in the program output"
		::= { dli3001c01v1Entry 13 }

		-- 1.3.6.1.4.1.10106.3.101291.1.1.15
		dli3001c01v1PgmInsLogo4 OBJECT-TYPE
			SYNTAX Bit0No1Yes
			MAX-ACCESS read-write
			STATUS current
			DESCRIPTION
				"Allows inserting the logo in the program output"
		::= { dli3001c01v1Entry 15 }

		-- 1.3.6.1.4.1.10106.3.101291.1.1.17
		dli3001c01v1PvwInsLogo1 OBJECT-TYPE
			SYNTAX Bit0No1Yes
			MAX-ACCESS read-write
			STATUS current
			DESCRIPTION
				"Allows inserting the logo in the preview output"
		::= { dli3001c01v1Entry 17 }

		-- 1.3.6.1.4.1.10106.3.101291.1.1.19
		dli3001c01v1PvwInsLogo2 OBJECT-TYPE
			SYNTAX Bit0No1Yes
			MAX-ACCESS read-write
			STATUS current
			DESCRIPTION
				"Allows inserting the logo in the preview output"
		::= { dli3001c01v1Entry 19 }

		-- 1.3.6.1.4.1.10106.3.101291.1.1.21
		dli3001c01v1PvwInsLogo3 OBJECT-TYPE
			SYNTAX Bit0No1Yes
			MAX-ACCESS read-write
			STATUS current
			DESCRIPTION
				"Allows inserting the logo in the preview output"
		::= { dli3001c01v1Entry 21 }

		-- 1.3.6.1.4.1.10106.3.101291.1.1.23
		dli3001c01v1PvwInsLogo4 OBJECT-TYPE
			SYNTAX Bit0No1Yes
			MAX-ACCESS read-write
			STATUS current
			DESCRIPTION
				"Allows inserting the logo in the preview output"
		::= { dli3001c01v1Entry 23 }

		-- 1.3.6.1.4.1.10106.3.101291.1.1.25
		dli3001c01v1MixAudio OBJECT-TYPE
			SYNTAX Bit0No1Yes
			MAX-ACCESS read-write
			STATUS current
			DESCRIPTION
				"Allows mixing the incomming audio with the internal generated audio"
		::= { dli3001c01v1Entry 25 }

		-- 1.3.6.1.4.1.10106.3.101291.1.1.27
		dli3001c01v1RestartAudio OBJECT-TYPE
			SYNTAX Bit0No1Yes
			MAX-ACCESS read-write
			STATUS current
			DESCRIPTION
				"Allows restarting the audio playback"
		::= { dli3001c01v1Entry 27 }

		-- 1.3.6.1.4.1.10106.3.101291.1.1.29
		dli3001c01v1SelLogo1 OBJECT-TYPE
			SYNTAX Uint6
			MAX-ACCESS read-write
			STATUS current
			DESCRIPTION
				"Allows selecting the logo to be inserted"
		::= { dli3001c01v1Entry 29 }

		-- 1.3.6.1.4.1.10106.3.101291.1.1.31
		dli3001c01v1SelLogo2 OBJECT-TYPE
			SYNTAX Uint6
			MAX-ACCESS read-write
			STATUS current
			DESCRIPTION
				"Allows selecting the logo to be inserted"
		::= { dli3001c01v1Entry 31 }

		-- 1.3.6.1.4.1.10106.3.101291.1.1.33
		dli3001c01v1SelLogo3 OBJECT-TYPE
			SYNTAX Uint6
			MAX-ACCESS read-write
			STATUS current
			DESCRIPTION
				"Allows selecting the logo to be inserted"
		::= { dli3001c01v1Entry 33 }

		-- 1.3.6.1.4.1.10106.3.101291.1.1.35
		dli3001c01v1SelLogo4 OBJECT-TYPE
			SYNTAX Uint6
			MAX-ACCESS read-write
			STATUS current
			DESCRIPTION
				"Allows selecting the logo to be inserted"
		::= { dli3001c01v1Entry 35 }

		-- 1.3.6.1.4.1.10106.3.101291.1.1.37
		dli3001c01v1Group OBJECT-TYPE
			SYNTAX EmbedGroup
			MAX-ACCESS read-write
			STATUS current
			DESCRIPTION
				"Allows selecting the group in which the audio is embedded"
		::= { dli3001c01v1Entry 37 }

		-- 1.3.6.1.4.1.10106.3.101291.1.1.39
		dli3001c01v1InsAudio OBJECT-TYPE
			SYNTAX Bit0No1Yes
			MAX-ACCESS read-write
			STATUS current
			DESCRIPTION
				"Allows inserting audio"
		::= { dli3001c01v1Entry 39 }

		-- 1.3.6.1.4.1.10106.3.101291.1.1.41
		dli3001c01v1EmbedBits OBJECT-TYPE
			SYNTAX Bit024120
			MAX-ACCESS read-write
			STATUS current
			DESCRIPTION
				"Allows selecting the number of bits of the embedded audio"
		::= { dli3001c01v1Entry 41 }

		-- 1.3.6.1.4.1.10106.3.101291.1.1.43
		dli3001c01v1CleanAudioGr1 OBJECT-TYPE
			SYNTAX Bit0No1Yes
			MAX-ACCESS read-write
			STATUS current
			DESCRIPTION
				"Allows cleaning audio group 1 packets"
		::= { dli3001c01v1Entry 43 }

		-- 1.3.6.1.4.1.10106.3.101291.1.1.45
		dli3001c01v1CleanAudioGr2 OBJECT-TYPE
			SYNTAX Bit0No1Yes
			MAX-ACCESS read-write
			STATUS current
			DESCRIPTION
				"Allows cleaning audio group 2 packets"
		::= { dli3001c01v1Entry 45 }

		-- 1.3.6.1.4.1.10106.3.101291.1.1.47
		dli3001c01v1CleanAudioGr3 OBJECT-TYPE
			SYNTAX Bit0No1Yes
			MAX-ACCESS read-write
			STATUS current
			DESCRIPTION
				"Allows cleaning audio group 3 packets"
		::= { dli3001c01v1Entry 47 }

		-- 1.3.6.1.4.1.10106.3.101291.1.1.49
		dli3001c01v1CleanAudioGr4 OBJECT-TYPE
			SYNTAX Bit0No1Yes
			MAX-ACCESS read-write
			STATUS current
			DESCRIPTION
				"Allows cleaning audio group 4 packets"
		::= { dli3001c01v1Entry 49 }

		-- 1.3.6.1.4.1.10106.3.101291.1.1.51
		dli3001c01v1GpiMode OBJECT-TYPE
			SYNTAX Bit0Lev1Edg
			MAX-ACCESS read-write
			STATUS current
			DESCRIPTION
				"Allows selecting the GPI activation mode"
		::= { dli3001c01v1Entry 51 }

		-- 1.3.6.1.4.1.10106.3.101291.1.1.53
		dli3001c01v1LoadLogo OBJECT-TYPE
			SYNTAX Bit0No1Yes
			MAX-ACCESS read-write
			STATUS current
			DESCRIPTION
				"Allows reloading the logo after a file transfer"
		::= { dli3001c01v1Entry 53 }

		-- 1.3.6.1.4.1.10106.3.101291.1.1.55
		dli3001c01v1PosHLogo1Msb OBJECT-TYPE
			SYNTAX Uint2
			MAX-ACCESS read-write
			STATUS current
			DESCRIPTION
				"Allows coarse adjust of logo horizontal position"
		::= { dli3001c01v1Entry 55 }

		-- 1.3.6.1.4.1.10106.3.101291.1.1.57
		dli3001c01v1PosHLogo1Lsb OBJECT-TYPE
			SYNTAX Uint8
			MAX-ACCESS read-write
			STATUS current
			DESCRIPTION
				"Allows fine adjust of logo horizontal position"
		::= { dli3001c01v1Entry 57 }

		-- 1.3.6.1.4.1.10106.3.101291.1.1.59
		dli3001c01v1PosVLogo1Msb OBJECT-TYPE
			SYNTAX Uint1
			MAX-ACCESS read-write
			STATUS current
			DESCRIPTION
				"Allows coarse adjust of logo vertical position"
		::= { dli3001c01v1Entry 59 }

		-- 1.3.6.1.4.1.10106.3.101291.1.1.61
		dli3001c01v1PosVLogo1Lsb OBJECT-TYPE
			SYNTAX Uint8
			MAX-ACCESS read-write
			STATUS current
			DESCRIPTION
				"Allows fine adjust of logo vertical position"
		::= { dli3001c01v1Entry 61 }

		-- 1.3.6.1.4.1.10106.3.101291.1.1.63
		dli3001c01v1PosHLogo2Msb OBJECT-TYPE
			SYNTAX Uint2
			MAX-ACCESS read-write
			STATUS current
			DESCRIPTION
				"Allows coarse adjust of logo horizontal position"
		::= { dli3001c01v1Entry 63 }

		-- 1.3.6.1.4.1.10106.3.101291.1.1.65
		dli3001c01v1PosHLogo2Lsb OBJECT-TYPE
			SYNTAX Uint7
			MAX-ACCESS read-write
			STATUS current
			DESCRIPTION
				"Allows fine adjust of logo horizontal position"
		::= { dli3001c01v1Entry 65 }

		-- 1.3.6.1.4.1.10106.3.101291.1.1.67
		dli3001c01v1PosVLogo2Msb OBJECT-TYPE
			SYNTAX Uint1
			MAX-ACCESS read-write
			STATUS current
			DESCRIPTION
				"Allows coarse adjust of logo vertical position"
		::= { dli3001c01v1Entry 67 }

		-- 1.3.6.1.4.1.10106.3.101291.1.1.69
		dli3001c01v1PosVLogo2Lsb OBJECT-TYPE
			SYNTAX Uint8
			MAX-ACCESS read-write
			STATUS current
			DESCRIPTION
				"Allows fine adjust of logo vertical position"
		::= { dli3001c01v1Entry 69 }

		-- 1.3.6.1.4.1.10106.3.101291.1.1.71
		dli3001c01v1PosHLogo3Msb OBJECT-TYPE
			SYNTAX Uint2
			MAX-ACCESS read-write
			STATUS current
			DESCRIPTION
				"Allows coarse adjust of logo horizontal position"
		::= { dli3001c01v1Entry 71 }

		-- 1.3.6.1.4.1.10106.3.101291.1.1.73
		dli3001c01v1PosHLogo3Lsb OBJECT-TYPE
			SYNTAX Uint7
			MAX-ACCESS read-write
			STATUS current
			DESCRIPTION
				"Allows fine adjust of logo horizontal position"
		::= { dli3001c01v1Entry 73 }

		-- 1.3.6.1.4.1.10106.3.101291.1.1.75
		dli3001c01v1PosVLogo3Msb OBJECT-TYPE
			SYNTAX Uint1
			MAX-ACCESS read-write
			STATUS current
			DESCRIPTION
				"Allows coarse adjust of logo vertical position"
		::= { dli3001c01v1Entry 75 }

		-- 1.3.6.1.4.1.10106.3.101291.1.1.77
		dli3001c01v1PosVLogo3Lsb OBJECT-TYPE
			SYNTAX Uint8
			MAX-ACCESS read-write
			STATUS current
			DESCRIPTION
				"Allows fine adjust of logo vertical position"
		::= { dli3001c01v1Entry 77 }

		-- 1.3.6.1.4.1.10106.3.101291.1.1.79
		dli3001c01v1PosHLogo4Msb OBJECT-TYPE
			SYNTAX Uint2
			MAX-ACCESS read-write
			STATUS current
			DESCRIPTION
				"Allows coarse adjust of logo horizontal position"
		::= { dli3001c01v1Entry 79 }

		-- 1.3.6.1.4.1.10106.3.101291.1.1.81
		dli3001c01v1PosHLogo4Lsb OBJECT-TYPE
			SYNTAX Uint7
			MAX-ACCESS read-write
			STATUS current
			DESCRIPTION
				"Allows fine adjust of logo horizontal position"
		::= { dli3001c01v1Entry 81 }

		-- 1.3.6.1.4.1.10106.3.101291.1.1.83
		dli3001c01v1PosVLogo4Msb OBJECT-TYPE
			SYNTAX Uint1
			MAX-ACCESS read-write
			STATUS current
			DESCRIPTION
				"Allows coarse adjust of logo vertical position"
		::= { dli3001c01v1Entry 83 }

		-- 1.3.6.1.4.1.10106.3.101291.1.1.85
		dli3001c01v1PosVLogo4Lsb OBJECT-TYPE
			SYNTAX Uint8
			MAX-ACCESS read-write
			STATUS current
			DESCRIPTION
				"Allows fine adjust of logo vertical position"
		::= { dli3001c01v1Entry 85 }

		-- 1.3.6.1.4.1.10106.3.101291.1.1.87
		dli3001c01v1NoSig OBJECT-TYPE
			SYNTAX BitFail
			MAX-ACCESS read-only
			STATUS current
			DESCRIPTION
				"SDI input signal status"
		::= { dli3001c01v1Entry 87 }

		-- 1.3.6.1.4.1.10106.3.101291.1.1.88
		dli3001c01v1NoSigTrapEnable OBJECT-TYPE
			SYNTAX AlarmEnable
			MAX-ACCESS read-write
			STATUS current
			DESCRIPTION
				"SDI input signal status Trap Enable"
		::= { dli3001c01v1Entry 88 }

		-- 1.3.6.1.4.1.10106.3.101291.1.1.89
		dli3001c01v1EdhErr OBJECT-TYPE
			SYNTAX BitFail
			MAX-ACCESS read-only
			STATUS current
			DESCRIPTION
				"Indicates EDH errors"
		::= { dli3001c01v1Entry 89 }

		-- 1.3.6.1.4.1.10106.3.101291.1.1.91
		dli3001c01v1AudioFr0Err OBJECT-TYPE
			SYNTAX BitFail
			MAX-ACCESS read-only
			STATUS current
			DESCRIPTION
				"Indicates that there is no valid audio in the frame 0"
		::= { dli3001c01v1Entry 91 }

		-- 1.3.6.1.4.1.10106.3.101291.1.1.92
		dli3001c01v1AudioFr0ErrTrapEnable OBJECT-TYPE
			SYNTAX AlarmEnable
			MAX-ACCESS read-write
			STATUS current
			DESCRIPTION
				"Indicates that there is no valid audio in the frame 0 Trap Enable"
		::= { dli3001c01v1Entry 92 }

		-- 1.3.6.1.4.1.10106.3.101291.1.1.93
		dli3001c01v1AudioFr1Err OBJECT-TYPE
			SYNTAX BitFail
			MAX-ACCESS read-only
			STATUS current
			DESCRIPTION
				"Indicates that there is no valid audio in the frame 1"
		::= { dli3001c01v1Entry 93 }

		-- 1.3.6.1.4.1.10106.3.101291.1.1.94
		dli3001c01v1AudioFr1ErrTrapEnable OBJECT-TYPE
			SYNTAX AlarmEnable
			MAX-ACCESS read-write
			STATUS current
			DESCRIPTION
				"Indicates that there is no valid audio in the frame 1 Trap Enable"
		::= { dli3001c01v1Entry 94 }

		-- 1.3.6.1.4.1.10106.3.101291.1.1.95
		dli3001c01v1AudioGr1 OBJECT-TYPE
			SYNTAX Bit0No1Yes
			MAX-ACCESS read-only
			STATUS current
			DESCRIPTION
				"Indicates the presence of packets of audio group 1"
		::= { dli3001c01v1Entry 95 }

		-- 1.3.6.1.4.1.10106.3.101291.1.1.97
		dli3001c01v1AudioGr2 OBJECT-TYPE
			SYNTAX Bit0No1Yes
			MAX-ACCESS read-only
			STATUS current
			DESCRIPTION
				"Indicates the presence of packets of audio group 2"
		::= { dli3001c01v1Entry 97 }

		-- 1.3.6.1.4.1.10106.3.101291.1.1.99
		dli3001c01v1AudioGr3 OBJECT-TYPE
			SYNTAX Bit0No1Yes
			MAX-ACCESS read-only
			STATUS current
			DESCRIPTION
				"Indicates the presence of packets of audio group 3"
		::= { dli3001c01v1Entry 99 }

		-- 1.3.6.1.4.1.10106.3.101291.1.1.101
		dli3001c01v1AudioGr4 OBJECT-TYPE
			SYNTAX Bit0No1Yes
			MAX-ACCESS read-only
			STATUS current
			DESCRIPTION
				"Indicates the presence of packets of audio group 4"
		::= { dli3001c01v1Entry 101 }

		-- 1.3.6.1.4.1.10106.3.259601
		eap3001c01v1 OBJECT IDENTIFIER ::= { albalaProducts 259601 }

		-- 1.3.6.1.4.1.10106.3.259601.1
		eap3001c01v1Table  OBJECT-TYPE
			SYNTAX SEQUENCE OF Eap3001c01v1Entry
			MAX-ACCESS not-accessible
			STATUS current
			DESCRIPTION
				"Module  EAP3001C01V1 Table"
			::= { eap3001c01v1 1 }

		-- 1.3.6.1.4.1.10106.3.259601.1.1
		eap3001c01v1Entry  OBJECT-TYPE
			SYNTAX Eap3001c01v1Entry
			MAX-ACCESS not-accessible
			STATUS current
			DESCRIPTION
				"Module EAP3001C01V1 Entry"
			INDEX { eap3001c01v1Index }
			::= { eap3001c01v1Table 1 }

			Eap3001c01v1Entry ::=
			SEQUENCE {
				eap3001c01v1Index
				ModuleIndex,
				eap3001c01v1ActivePreset
				PresetActive,
				eap3001c01v1LoadPreset
				PresetLoad,
				eap3001c01v1SavePreset
				PresetSave,
				eap3001c01v1InsGroupA
				EmbedGroup,
				eap3001c01v1InsAudioA
				Bit0No1Yes,
				eap3001c01v1EmbedBitsA
				Bit024120,
				eap3001c01v1InsGroupB
				EmbedGroup,
				eap3001c01v1InsAudioB
				Bit0No1Yes,
				eap3001c01v1EmbedBitsB
				Bit024120,
				eap3001c01v1RdGroupA
				EmbedGroup,
				eap3001c01v1RdGroupB
				EmbedGroup,
				eap3001c01v1CleanAudioGr1
				Bit0No1Yes,
				eap3001c01v1CleanAudioGr2
				Bit0No1Yes,
				eap3001c01v1CleanAudioGr3
				Bit0No1Yes,
				eap3001c01v1CleanAudioGr4
				Bit0No1Yes,
				eap3001c01v1GpiMode
				Bit0Lev1Edg,
				eap3001c01v1AuxiliarInput
				ChgOverInput2,
				eap3001c01v1GainAO1I1
				Gain24dbMute,
				eap3001c01v1PhaseAO1I1
				Bit0Nor1Inv,
				eap3001c01v1GainAO1I2
				Gain24dbMute,
				eap3001c01v1PhaseAO1I2
				Bit0Nor1Inv,
				eap3001c01v1GainAO1I3
				Gain24dbMute,
				eap3001c01v1PhaseAO1I3
				Bit0Nor1Inv,
				eap3001c01v1GainAO1I4
				Gain24dbMute,
				eap3001c01v1PhaseAO1I4
				Bit0Nor1Inv,
				eap3001c01v1GainAO1I5
				Gain24dbMute,
				eap3001c01v1PhaseAO1I5
				Bit0Nor1Inv,
				eap3001c01v1GainAO1I6
				Gain24dbMute,
				eap3001c01v1PhaseAO1I6
				Bit0Nor1Inv,
				eap3001c01v1GainAO1I7
				Gain24dbMute,
				eap3001c01v1PhaseAO1I7
				Bit0Nor1Inv,
				eap3001c01v1GainAO1I8
				Gain24dbMute,
				eap3001c01v1PhaseAO1I8
				Bit0Nor1Inv,
				eap3001c01v1GainAO2I1
				Gain24dbMute,
				eap3001c01v1PhaseAO2I1
				Bit0Nor1Inv,
				eap3001c01v1GainAO2I2
				Gain24dbMute,
				eap3001c01v1PhaseAO2I2
				Bit0Nor1Inv,
				eap3001c01v1GainAO2I3
				Gain24dbMute,
				eap3001c01v1PhaseAO2I3
				Bit0Nor1Inv,
				eap3001c01v1GainAO2I4
				Gain24dbMute,
				eap3001c01v1PhaseAO2I4
				Bit0Nor1Inv,
				eap3001c01v1GainAO2I5
				Gain24dbMute,
				eap3001c01v1PhaseAO2I5
				Bit0Nor1Inv,
				eap3001c01v1GainAO2I6
				Gain24dbMute,
				eap3001c01v1PhaseAO2I6
				Bit0Nor1Inv,
				eap3001c01v1GainAO2I7
				Gain24dbMute,
				eap3001c01v1PhaseAO2I7
				Bit0Nor1Inv,
				eap3001c01v1GainAO2I8
				Gain24dbMute,
				eap3001c01v1PhaseAO2I8
				Bit0Nor1Inv,
				eap3001c01v1GainAO3I1
				Gain24dbMute,
				eap3001c01v1PhaseAO3I1
				Bit0Nor1Inv,
				eap3001c01v1GainAO3I2
				Gain24dbMute,
				eap3001c01v1PhaseAO3I2
				Bit0Nor1Inv,
				eap3001c01v1GainAO3I3
				Gain24dbMute,
				eap3001c01v1PhaseAO3I3
				Bit0Nor1Inv,
				eap3001c01v1GainAO3I4
				Gain24dbMute,
				eap3001c01v1PhaseAO3I4
				Bit0Nor1Inv,
				eap3001c01v1GainAO3I5
				Gain24dbMute,
				eap3001c01v1PhaseAO3I5
				Bit0Nor1Inv,
				eap3001c01v1GainAO3I6
				Gain24dbMute,
				eap3001c01v1PhaseAO3I6
				Bit0Nor1Inv,
				eap3001c01v1GainAO3I7
				Gain24dbMute,
				eap3001c01v1PhaseAO3I7
				Bit0Nor1Inv,
				eap3001c01v1GainAO3I8
				Gain24dbMute,
				eap3001c01v1PhaseAO3I8
				Bit0Nor1Inv,
				eap3001c01v1GainAO4I1
				Gain24dbMute,
				eap3001c01v1PhaseAO4I1
				Bit0Nor1Inv,
				eap3001c01v1GainAO4I2
				Gain24dbMute,
				eap3001c01v1PhaseAO4I2
				Bit0Nor1Inv,
				eap3001c01v1GainAO4I3
				Gain24dbMute,
				eap3001c01v1PhaseAO4I3
				Bit0Nor1Inv,
				eap3001c01v1GainAO4I4
				Gain24dbMute,
				eap3001c01v1PhaseAO4I4
				Bit0Nor1Inv,
				eap3001c01v1GainAO4I5
				Gain24dbMute,
				eap3001c01v1PhaseAO4I5
				Bit0Nor1Inv,
				eap3001c01v1GainAO4I6
				Gain24dbMute,
				eap3001c01v1PhaseAO4I6
				Bit0Nor1Inv,
				eap3001c01v1GainAO4I7
				Gain24dbMute,
				eap3001c01v1PhaseAO4I7
				Bit0Nor1Inv,
				eap3001c01v1GainAO4I8
				Gain24dbMute,
				eap3001c01v1PhaseAO4I8
				Bit0Nor1Inv,
				eap3001c01v1DelayAO1Msb
				DelayX256Sampl,
				eap3001c01v1DelayAO1Lsb
				DelaySamp2,
				eap3001c01v1DelayAO2Msb
				DelayX256Sampl,
				eap3001c01v1DelayAO2Lsb
				DelaySamp2,
				eap3001c01v1DelayAO3Msb
				DelayX256Sampl,
				eap3001c01v1DelayAO3Lsb
				DelaySamp2,
				eap3001c01v1DelayAO4Msb
				DelayX256Sampl,
				eap3001c01v1DelayAO4Lsb
				DelaySamp2,
				eap3001c01v1GainBO1I1
				Gain24dbMute,
				eap3001c01v1PhaseBO1I1
				Bit0Nor1Inv,
				eap3001c01v1GainBO1I2
				Gain24dbMute,
				eap3001c01v1PhaseBO1I2
				Bit0Nor1Inv,
				eap3001c01v1GainBO1I3
				Gain24dbMute,
				eap3001c01v1PhaseBO1I3
				Bit0Nor1Inv,
				eap3001c01v1GainBO1I4
				Gain24dbMute,
				eap3001c01v1PhaseBO1I4
				Bit0Nor1Inv,
				eap3001c01v1GainBO1I5
				Gain24dbMute,
				eap3001c01v1PhaseBO1I5
				Bit0Nor1Inv,
				eap3001c01v1GainBO1I6
				Gain24dbMute,
				eap3001c01v1PhaseBO1I6
				Bit0Nor1Inv,
				eap3001c01v1GainBO1I7
				Gain24dbMute,
				eap3001c01v1PhaseBO1I7
				Bit0Nor1Inv,
				eap3001c01v1GainBO1I8
				Gain24dbMute,
				eap3001c01v1PhaseBO1I8
				Bit0Nor1Inv,
				eap3001c01v1GainBO2I1
				Gain24dbMute,
				eap3001c01v1PhaseBO2I1
				Bit0Nor1Inv,
				eap3001c01v1GainBO2I2
				Gain24dbMute,
				eap3001c01v1PhaseBO2I2
				Bit0Nor1Inv,
				eap3001c01v1GainBO2I3
				Gain24dbMute,
				eap3001c01v1PhaseBO2I3
				Bit0Nor1Inv,
				eap3001c01v1GainBO2I4
				Gain24dbMute,
				eap3001c01v1PhaseBO2I4
				Bit0Nor1Inv,
				eap3001c01v1GainBO2I5
				Gain24dbMute,
				eap3001c01v1PhaseBO2I5
				Bit0Nor1Inv,
				eap3001c01v1GainBO2I6
				Gain24dbMute,
				eap3001c01v1PhaseBO2I6
				Bit0Nor1Inv,
				eap3001c01v1GainBO2I7
				Gain24dbMute,
				eap3001c01v1PhaseBO2I7
				Bit0Nor1Inv,
				eap3001c01v1GainBO2I8
				Gain24dbMute,
				eap3001c01v1PhaseBO2I8
				Bit0Nor1Inv,
				eap3001c01v1GainBO3I1
				Gain24dbMute,
				eap3001c01v1PhaseBO3I1
				Bit0Nor1Inv,
				eap3001c01v1GainBO3I2
				Gain24dbMute,
				eap3001c01v1PhaseBO3I2
				Bit0Nor1Inv,
				eap3001c01v1GainBO3I3
				Gain24dbMute,
				eap3001c01v1PhaseBO3I3
				Bit0Nor1Inv,
				eap3001c01v1GainBO3I4
				Gain24dbMute,
				eap3001c01v1PhaseBO3I4
				Bit0Nor1Inv,
				eap3001c01v1GainBO3I5
				Gain24dbMute,
				eap3001c01v1PhaseBO3I5
				Bit0Nor1Inv,
				eap3001c01v1GainBO3I6
				Gain24dbMute,
				eap3001c01v1PhaseBO3I6
				Bit0Nor1Inv,
				eap3001c01v1GainBO3I7
				Gain24dbMute,
				eap3001c01v1PhaseBO3I7
				Bit0Nor1Inv,
				eap3001c01v1GainBO3I8
				Gain24dbMute,
				eap3001c01v1PhaseBO3I8
				Bit0Nor1Inv,
				eap3001c01v1GainBO4I1
				Gain24dbMute,
				eap3001c01v1PhaseBO4I1
				Bit0Nor1Inv,
				eap3001c01v1GainBO4I2
				Gain24dbMute,
				eap3001c01v1PhaseBO4I2
				Bit0Nor1Inv,
				eap3001c01v1GainBO4I3
				Gain24dbMute,
				eap3001c01v1PhaseBO4I3
				Bit0Nor1Inv,
				eap3001c01v1GainBO4I4
				Gain24dbMute,
				eap3001c01v1PhaseBO4I4
				Bit0Nor1Inv,
				eap3001c01v1GainBO4I5
				Gain24dbMute,
				eap3001c01v1PhaseBO4I5
				Bit0Nor1Inv,
				eap3001c01v1GainBO4I6
				Gain24dbMute,
				eap3001c01v1PhaseBO4I6
				Bit0Nor1Inv,
				eap3001c01v1GainBO4I7
				Gain24dbMute,
				eap3001c01v1PhaseBO4I7
				Bit0Nor1Inv,
				eap3001c01v1GainBO4I8
				Gain24dbMute,
				eap3001c01v1PhaseBO4I8
				Bit0Nor1Inv,
				eap3001c01v1DelayBO1Msb
				DelayX256Sampl,
				eap3001c01v1DelayBO1Lsb
				DelaySamp2,
				eap3001c01v1DelayBO2Msb
				DelayX256Sampl,
				eap3001c01v1DelayBO2Lsb
				DelaySamp2,
				eap3001c01v1DelayBO3Msb
				DelayX256Sampl,
				eap3001c01v1DelayBO3Lsb
				DelaySamp2,
				eap3001c01v1DelayBO4Msb
				DelayX256Sampl,
				eap3001c01v1DelayBO4Lsb
				DelaySamp2,
				eap3001c01v1NoSigA
				BitFail,
				eap3001c01v1NoSigATrapEnable
				AlarmEnable,
				eap3001c01v1EdhErrA
				BitFail,
				eap3001c01v1AudioFr0ErrA
				BitFail,
				eap3001c01v1AudioFr0ErrATrapEnable
				AlarmEnable,
				eap3001c01v1AudioFr1ErrA
				BitFail,
				eap3001c01v1AudioFr1ErrATrapEnable
				AlarmEnable,
				eap3001c01v1AudioGr1A
				Bit0No1Yes,
				eap3001c01v1AudioGr2A
				Bit0No1Yes,
				eap3001c01v1AudioGr3A
				Bit0No1Yes,
				eap3001c01v1AudioGr4A
				Bit0No1Yes,
				eap3001c01v1NoSigB
				BitFail,
				eap3001c01v1NoSigBTrapEnable
				AlarmEnable,
				eap3001c01v1EdhErrB
				BitFail,
				eap3001c01v1AudioFr0ErrB
				BitFail,
				eap3001c01v1AudioFr0ErrBTrapEnable
				AlarmEnable,
				eap3001c01v1AudioFr1ErrB
				BitFail,
				eap3001c01v1AudioFr1ErrBTrapEnable
				AlarmEnable,
				eap3001c01v1AudioGr1B
				Bit0No1Yes,
				eap3001c01v1AudioGr2B
				Bit0No1Yes,
				eap3001c01v1AudioGr3B
				Bit0No1Yes,
				eap3001c01v1AudioGr4B
				Bit0No1Yes
			 }

		-- 1.3.6.1.4.1.10106.3.101291.1.1.1
		eap3001c01v1Index OBJECT-TYPE
			SYNTAX ModuleIndex
			MAX-ACCESS read-only
			STATUS current
			DESCRIPTION
				"Index of EAP3001C01V1 Table"
		::= { eap3001c01v1Entry 1 }

		-- 1.3.6.1.4.1.10106.3.101291.1.1.3
		eap3001c01v1ActivePreset OBJECT-TYPE
			SYNTAX PresetActive
			MAX-ACCESS read-only
			STATUS current
			DESCRIPTION
				"Shows the active preset"
		::= { eap3001c01v1Entry 3 }

		-- 1.3.6.1.4.1.10106.3.101291.1.1.5
		eap3001c01v1LoadPreset OBJECT-TYPE
			SYNTAX PresetLoad
			MAX-ACCESS read-write
			STATUS current
			DESCRIPTION
				"Allows loading a preset"
		::= { eap3001c01v1Entry 5 }

		-- 1.3.6.1.4.1.10106.3.101291.1.1.7
		eap3001c01v1SavePreset OBJECT-TYPE
			SYNTAX PresetSave
			MAX-ACCESS read-write
			STATUS current
			DESCRIPTION
				"Allows saving a preset"
		::= { eap3001c01v1Entry 7 }

		-- 1.3.6.1.4.1.10106.3.101291.1.1.9
		eap3001c01v1InsGroupA OBJECT-TYPE
			SYNTAX EmbedGroup
			MAX-ACCESS read-write
			STATUS current
			DESCRIPTION
				"Allows selecting the group for the embedder A"
		::= { eap3001c01v1Entry 9 }

		-- 1.3.6.1.4.1.10106.3.101291.1.1.11
		eap3001c01v1InsAudioA OBJECT-TYPE
			SYNTAX Bit0No1Yes
			MAX-ACCESS read-write
			STATUS current
			DESCRIPTION
				"Allows enabling the embedder A"
		::= { eap3001c01v1Entry 11 }

		-- 1.3.6.1.4.1.10106.3.101291.1.1.13
		eap3001c01v1EmbedBitsA OBJECT-TYPE
			SYNTAX Bit024120
			MAX-ACCESS read-write
			STATUS current
			DESCRIPTION
				"Allows selecting the number of bits of the embedder A"
		::= { eap3001c01v1Entry 13 }

		-- 1.3.6.1.4.1.10106.3.101291.1.1.15
		eap3001c01v1InsGroupB OBJECT-TYPE
			SYNTAX EmbedGroup
			MAX-ACCESS read-write
			STATUS current
			DESCRIPTION
				"Allows selecting the group for the embedder B"
		::= { eap3001c01v1Entry 15 }

		-- 1.3.6.1.4.1.10106.3.101291.1.1.17
		eap3001c01v1InsAudioB OBJECT-TYPE
			SYNTAX Bit0No1Yes
			MAX-ACCESS read-write
			STATUS current
			DESCRIPTION
				"Allows enabling the embedder B"
		::= { eap3001c01v1Entry 17 }

		-- 1.3.6.1.4.1.10106.3.101291.1.1.19
		eap3001c01v1EmbedBitsB OBJECT-TYPE
			SYNTAX Bit024120
			MAX-ACCESS read-write
			STATUS current
			DESCRIPTION
				"Allows selecting the number of bits of the embedder B"
		::= { eap3001c01v1Entry 19 }

		-- 1.3.6.1.4.1.10106.3.101291.1.1.21
		eap3001c01v1RdGroupA OBJECT-TYPE
			SYNTAX EmbedGroup
			MAX-ACCESS read-write
			STATUS current
			DESCRIPTION
				"Allows selecting the group for the deembedder"
		::= { eap3001c01v1Entry 21 }

		-- 1.3.6.1.4.1.10106.3.101291.1.1.23
		eap3001c01v1RdGroupB OBJECT-TYPE
			SYNTAX EmbedGroup
			MAX-ACCESS read-write
			STATUS current
			DESCRIPTION
				"Allows selecting the group for the deembedder"
		::= { eap3001c01v1Entry 23 }

		-- 1.3.6.1.4.1.10106.3.101291.1.1.25
		eap3001c01v1CleanAudioGr1 OBJECT-TYPE
			SYNTAX Bit0No1Yes
			MAX-ACCESS read-write
			STATUS current
			DESCRIPTION
				"Allows cleaning audio group 1 packets"
		::= { eap3001c01v1Entry 25 }

		-- 1.3.6.1.4.1.10106.3.101291.1.1.27
		eap3001c01v1CleanAudioGr2 OBJECT-TYPE
			SYNTAX Bit0No1Yes
			MAX-ACCESS read-write
			STATUS current
			DESCRIPTION
				"Allows cleaning audio group 2 packets"
		::= { eap3001c01v1Entry 27 }

		-- 1.3.6.1.4.1.10106.3.101291.1.1.29
		eap3001c01v1CleanAudioGr3 OBJECT-TYPE
			SYNTAX Bit0No1Yes
			MAX-ACCESS read-write
			STATUS current
			DESCRIPTION
				"Allows cleaning audio group 3 packets"
		::= { eap3001c01v1Entry 29 }

		-- 1.3.6.1.4.1.10106.3.101291.1.1.31
		eap3001c01v1CleanAudioGr4 OBJECT-TYPE
			SYNTAX Bit0No1Yes
			MAX-ACCESS read-write
			STATUS current
			DESCRIPTION
				"Allows cleaning audio group 4 packets"
		::= { eap3001c01v1Entry 31 }

		-- 1.3.6.1.4.1.10106.3.101291.1.1.33
		eap3001c01v1GpiMode OBJECT-TYPE
			SYNTAX Bit0Lev1Edg
			MAX-ACCESS read-write
			STATUS current
			DESCRIPTION
				"Allows selecting the GPI activation mode"
		::= { eap3001c01v1Entry 33 }

		-- 1.3.6.1.4.1.10106.3.101291.1.1.35
		eap3001c01v1AuxiliarInput OBJECT-TYPE
			SYNTAX ChgOverInput2
			MAX-ACCESS read-write
			STATUS current
			DESCRIPTION
				"Allows selecting the input to the second deembedder"
		::= { eap3001c01v1Entry 35 }

		-- 1.3.6.1.4.1.10106.3.101291.1.1.37
		eap3001c01v1GainAO1I1 OBJECT-TYPE
			SYNTAX Gain24dbMute
			MAX-ACCESS read-write
			STATUS current
			DESCRIPTION
				"Gain input A ch.1"
		::= { eap3001c01v1Entry 37 }

		-- 1.3.6.1.4.1.10106.3.101291.1.1.39
		eap3001c01v1PhaseAO1I1 OBJECT-TYPE
			SYNTAX Bit0Nor1Inv
			MAX-ACCESS read-write
			STATUS current
			DESCRIPTION
				"Phase input A ch.1"
		::= { eap3001c01v1Entry 39 }

		-- 1.3.6.1.4.1.10106.3.101291.1.1.41
		eap3001c01v1GainAO1I2 OBJECT-TYPE
			SYNTAX Gain24dbMute
			MAX-ACCESS read-write
			STATUS current
			DESCRIPTION
				"Gain input A ch.2"
		::= { eap3001c01v1Entry 41 }

		-- 1.3.6.1.4.1.10106.3.101291.1.1.43
		eap3001c01v1PhaseAO1I2 OBJECT-TYPE
			SYNTAX Bit0Nor1Inv
			MAX-ACCESS read-write
			STATUS current
			DESCRIPTION
				"Phase input A ch.2"
		::= { eap3001c01v1Entry 43 }

		-- 1.3.6.1.4.1.10106.3.101291.1.1.45
		eap3001c01v1GainAO1I3 OBJECT-TYPE
			SYNTAX Gain24dbMute
			MAX-ACCESS read-write
			STATUS current
			DESCRIPTION
				"Gain input A ch.3"
		::= { eap3001c01v1Entry 45 }

		-- 1.3.6.1.4.1.10106.3.101291.1.1.47
		eap3001c01v1PhaseAO1I3 OBJECT-TYPE
			SYNTAX Bit0Nor1Inv
			MAX-ACCESS read-write
			STATUS current
			DESCRIPTION
				"Phase input A ch.3"
		::= { eap3001c01v1Entry 47 }

		-- 1.3.6.1.4.1.10106.3.101291.1.1.49
		eap3001c01v1GainAO1I4 OBJECT-TYPE
			SYNTAX Gain24dbMute
			MAX-ACCESS read-write
			STATUS current
			DESCRIPTION
				"Gain input A ch.4"
		::= { eap3001c01v1Entry 49 }

		-- 1.3.6.1.4.1.10106.3.101291.1.1.51
		eap3001c01v1PhaseAO1I4 OBJECT-TYPE
			SYNTAX Bit0Nor1Inv
			MAX-ACCESS read-write
			STATUS current
			DESCRIPTION
				"Phase input A ch.4"
		::= { eap3001c01v1Entry 51 }

		-- 1.3.6.1.4.1.10106.3.101291.1.1.53
		eap3001c01v1GainAO1I5 OBJECT-TYPE
			SYNTAX Gain24dbMute
			MAX-ACCESS read-write
			STATUS current
			DESCRIPTION
				"Gain input B ch.1"
		::= { eap3001c01v1Entry 53 }

		-- 1.3.6.1.4.1.10106.3.101291.1.1.55
		eap3001c01v1PhaseAO1I5 OBJECT-TYPE
			SYNTAX Bit0Nor1Inv
			MAX-ACCESS read-write
			STATUS current
			DESCRIPTION
				"Phase input B ch.1"
		::= { eap3001c01v1Entry 55 }

		-- 1.3.6.1.4.1.10106.3.101291.1.1.57
		eap3001c01v1GainAO1I6 OBJECT-TYPE
			SYNTAX Gain24dbMute
			MAX-ACCESS read-write
			STATUS current
			DESCRIPTION
				"Gain input B ch.2"
		::= { eap3001c01v1Entry 57 }

		-- 1.3.6.1.4.1.10106.3.101291.1.1.59
		eap3001c01v1PhaseAO1I6 OBJECT-TYPE
			SYNTAX Bit0Nor1Inv
			MAX-ACCESS read-write
			STATUS current
			DESCRIPTION
				"Phase input B ch.2"
		::= { eap3001c01v1Entry 59 }

		-- 1.3.6.1.4.1.10106.3.101291.1.1.61
		eap3001c01v1GainAO1I7 OBJECT-TYPE
			SYNTAX Gain24dbMute
			MAX-ACCESS read-write
			STATUS current
			DESCRIPTION
				"Gain input B ch.3"
		::= { eap3001c01v1Entry 61 }

		-- 1.3.6.1.4.1.10106.3.101291.1.1.63
		eap3001c01v1PhaseAO1I7 OBJECT-TYPE
			SYNTAX Bit0Nor1Inv
			MAX-ACCESS read-write
			STATUS current
			DESCRIPTION
				"Phase input B ch.3"
		::= { eap3001c01v1Entry 63 }

		-- 1.3.6.1.4.1.10106.3.101291.1.1.65
		eap3001c01v1GainAO1I8 OBJECT-TYPE
			SYNTAX Gain24dbMute
			MAX-ACCESS read-write
			STATUS current
			DESCRIPTION
				"Gain input B ch.4"
		::= { eap3001c01v1Entry 65 }

		-- 1.3.6.1.4.1.10106.3.101291.1.1.67
		eap3001c01v1PhaseAO1I8 OBJECT-TYPE
			SYNTAX Bit0Nor1Inv
			MAX-ACCESS read-write
			STATUS current
			DESCRIPTION
				"Phase input B ch.4"
		::= { eap3001c01v1Entry 67 }

		-- 1.3.6.1.4.1.10106.3.101291.1.1.69
		eap3001c01v1GainAO2I1 OBJECT-TYPE
			SYNTAX Gain24dbMute
			MAX-ACCESS read-write
			STATUS current
			DESCRIPTION
				"Gain input A ch.1"
		::= { eap3001c01v1Entry 69 }

		-- 1.3.6.1.4.1.10106.3.101291.1.1.71
		eap3001c01v1PhaseAO2I1 OBJECT-TYPE
			SYNTAX Bit0Nor1Inv
			MAX-ACCESS read-write
			STATUS current
			DESCRIPTION
				"Phase input A ch.1"
		::= { eap3001c01v1Entry 71 }

		-- 1.3.6.1.4.1.10106.3.101291.1.1.73
		eap3001c01v1GainAO2I2 OBJECT-TYPE
			SYNTAX Gain24dbMute
			MAX-ACCESS read-write
			STATUS current
			DESCRIPTION
				"Gain input A ch.2"
		::= { eap3001c01v1Entry 73 }

		-- 1.3.6.1.4.1.10106.3.101291.1.1.75
		eap3001c01v1PhaseAO2I2 OBJECT-TYPE
			SYNTAX Bit0Nor1Inv
			MAX-ACCESS read-write
			STATUS current
			DESCRIPTION
				"Phase input A ch.2"
		::= { eap3001c01v1Entry 75 }

		-- 1.3.6.1.4.1.10106.3.101291.1.1.77
		eap3001c01v1GainAO2I3 OBJECT-TYPE
			SYNTAX Gain24dbMute
			MAX-ACCESS read-write
			STATUS current
			DESCRIPTION
				"Gain input A ch.3"
		::= { eap3001c01v1Entry 77 }

		-- 1.3.6.1.4.1.10106.3.101291.1.1.79
		eap3001c01v1PhaseAO2I3 OBJECT-TYPE
			SYNTAX Bit0Nor1Inv
			MAX-ACCESS read-write
			STATUS current
			DESCRIPTION
				"Phase input A ch.3"
		::= { eap3001c01v1Entry 79 }

		-- 1.3.6.1.4.1.10106.3.101291.1.1.81
		eap3001c01v1GainAO2I4 OBJECT-TYPE
			SYNTAX Gain24dbMute
			MAX-ACCESS read-write
			STATUS current
			DESCRIPTION
				"Gain input A ch.4"
		::= { eap3001c01v1Entry 81 }

		-- 1.3.6.1.4.1.10106.3.101291.1.1.83
		eap3001c01v1PhaseAO2I4 OBJECT-TYPE
			SYNTAX Bit0Nor1Inv
			MAX-ACCESS read-write
			STATUS current
			DESCRIPTION
				"Phase input A ch.4"
		::= { eap3001c01v1Entry 83 }

		-- 1.3.6.1.4.1.10106.3.101291.1.1.85
		eap3001c01v1GainAO2I5 OBJECT-TYPE
			SYNTAX Gain24dbMute
			MAX-ACCESS read-write
			STATUS current
			DESCRIPTION
				"Gain input B ch.1"
		::= { eap3001c01v1Entry 85 }

		-- 1.3.6.1.4.1.10106.3.101291.1.1.87
		eap3001c01v1PhaseAO2I5 OBJECT-TYPE
			SYNTAX Bit0Nor1Inv
			MAX-ACCESS read-write
			STATUS current
			DESCRIPTION
				"Phase input B ch.1"
		::= { eap3001c01v1Entry 87 }

		-- 1.3.6.1.4.1.10106.3.101291.1.1.89
		eap3001c01v1GainAO2I6 OBJECT-TYPE
			SYNTAX Gain24dbMute
			MAX-ACCESS read-write
			STATUS current
			DESCRIPTION
				"Gain input B ch.2"
		::= { eap3001c01v1Entry 89 }

		-- 1.3.6.1.4.1.10106.3.101291.1.1.91
		eap3001c01v1PhaseAO2I6 OBJECT-TYPE
			SYNTAX Bit0Nor1Inv
			MAX-ACCESS read-write
			STATUS current
			DESCRIPTION
				"Phase input B ch.2"
		::= { eap3001c01v1Entry 91 }

		-- 1.3.6.1.4.1.10106.3.101291.1.1.93
		eap3001c01v1GainAO2I7 OBJECT-TYPE
			SYNTAX Gain24dbMute
			MAX-ACCESS read-write
			STATUS current
			DESCRIPTION
				"Gain input B ch.3"
		::= { eap3001c01v1Entry 93 }

		-- 1.3.6.1.4.1.10106.3.101291.1.1.95
		eap3001c01v1PhaseAO2I7 OBJECT-TYPE
			SYNTAX Bit0Nor1Inv
			MAX-ACCESS read-write
			STATUS current
			DESCRIPTION
				"Phase input B ch.3"
		::= { eap3001c01v1Entry 95 }

		-- 1.3.6.1.4.1.10106.3.101291.1.1.97
		eap3001c01v1GainAO2I8 OBJECT-TYPE
			SYNTAX Gain24dbMute
			MAX-ACCESS read-write
			STATUS current
			DESCRIPTION
				"Gain input B ch.4"
		::= { eap3001c01v1Entry 97 }

		-- 1.3.6.1.4.1.10106.3.101291.1.1.99
		eap3001c01v1PhaseAO2I8 OBJECT-TYPE
			SYNTAX Bit0Nor1Inv
			MAX-ACCESS read-write
			STATUS current
			DESCRIPTION
				"Phase input B ch.4"
		::= { eap3001c01v1Entry 99 }

		-- 1.3.6.1.4.1.10106.3.101291.1.1.101
		eap3001c01v1GainAO3I1 OBJECT-TYPE
			SYNTAX Gain24dbMute
			MAX-ACCESS read-write
			STATUS current
			DESCRIPTION
				"Gain input A ch.1"
		::= { eap3001c01v1Entry 101 }

		-- 1.3.6.1.4.1.10106.3.101291.1.1.103
		eap3001c01v1PhaseAO3I1 OBJECT-TYPE
			SYNTAX Bit0Nor1Inv
			MAX-ACCESS read-write
			STATUS current
			DESCRIPTION
				"Phase input A ch.1"
		::= { eap3001c01v1Entry 103 }

		-- 1.3.6.1.4.1.10106.3.101291.1.1.105
		eap3001c01v1GainAO3I2 OBJECT-TYPE
			SYNTAX Gain24dbMute
			MAX-ACCESS read-write
			STATUS current
			DESCRIPTION
				"Gain input A ch.2"
		::= { eap3001c01v1Entry 105 }

		-- 1.3.6.1.4.1.10106.3.101291.1.1.107
		eap3001c01v1PhaseAO3I2 OBJECT-TYPE
			SYNTAX Bit0Nor1Inv
			MAX-ACCESS read-write
			STATUS current
			DESCRIPTION
				"Phase input A ch.2"
		::= { eap3001c01v1Entry 107 }

		-- 1.3.6.1.4.1.10106.3.101291.1.1.109
		eap3001c01v1GainAO3I3 OBJECT-TYPE
			SYNTAX Gain24dbMute
			MAX-ACCESS read-write
			STATUS current
			DESCRIPTION
				"Gain input A ch.3"
		::= { eap3001c01v1Entry 109 }

		-- 1.3.6.1.4.1.10106.3.101291.1.1.111
		eap3001c01v1PhaseAO3I3 OBJECT-TYPE
			SYNTAX Bit0Nor1Inv
			MAX-ACCESS read-write
			STATUS current
			DESCRIPTION
				"Phase input A ch.3"
		::= { eap3001c01v1Entry 111 }

		-- 1.3.6.1.4.1.10106.3.101291.1.1.113
		eap3001c01v1GainAO3I4 OBJECT-TYPE
			SYNTAX Gain24dbMute
			MAX-ACCESS read-write
			STATUS current
			DESCRIPTION
				"Gain input A ch.4"
		::= { eap3001c01v1Entry 113 }

		-- 1.3.6.1.4.1.10106.3.101291.1.1.115
		eap3001c01v1PhaseAO3I4 OBJECT-TYPE
			SYNTAX Bit0Nor1Inv
			MAX-ACCESS read-write
			STATUS current
			DESCRIPTION
				"Phase input A ch.4"
		::= { eap3001c01v1Entry 115 }

		-- 1.3.6.1.4.1.10106.3.101291.1.1.117
		eap3001c01v1GainAO3I5 OBJECT-TYPE
			SYNTAX Gain24dbMute
			MAX-ACCESS read-write
			STATUS current
			DESCRIPTION
				"Gain input B ch.1"
		::= { eap3001c01v1Entry 117 }

		-- 1.3.6.1.4.1.10106.3.101291.1.1.119
		eap3001c01v1PhaseAO3I5 OBJECT-TYPE
			SYNTAX Bit0Nor1Inv
			MAX-ACCESS read-write
			STATUS current
			DESCRIPTION
				"Phase input B ch.1"
		::= { eap3001c01v1Entry 119 }

		-- 1.3.6.1.4.1.10106.3.101291.1.1.121
		eap3001c01v1GainAO3I6 OBJECT-TYPE
			SYNTAX Gain24dbMute
			MAX-ACCESS read-write
			STATUS current
			DESCRIPTION
				"Gain input B ch.2"
		::= { eap3001c01v1Entry 121 }

		-- 1.3.6.1.4.1.10106.3.101291.1.1.123
		eap3001c01v1PhaseAO3I6 OBJECT-TYPE
			SYNTAX Bit0Nor1Inv
			MAX-ACCESS read-write
			STATUS current
			DESCRIPTION
				"Phase input B ch.2"
		::= { eap3001c01v1Entry 123 }

		-- 1.3.6.1.4.1.10106.3.101291.1.1.125
		eap3001c01v1GainAO3I7 OBJECT-TYPE
			SYNTAX Gain24dbMute
			MAX-ACCESS read-write
			STATUS current
			DESCRIPTION
				"Gain input B ch.3"
		::= { eap3001c01v1Entry 125 }

		-- 1.3.6.1.4.1.10106.3.101291.1.1.127
		eap3001c01v1PhaseAO3I7 OBJECT-TYPE
			SYNTAX Bit0Nor1Inv
			MAX-ACCESS read-write
			STATUS current
			DESCRIPTION
				"Phase input B ch.3"
		::= { eap3001c01v1Entry 127 }

		-- 1.3.6.1.4.1.10106.3.101291.1.1.129
		eap3001c01v1GainAO3I8 OBJECT-TYPE
			SYNTAX Gain24dbMute
			MAX-ACCESS read-write
			STATUS current
			DESCRIPTION
				"Gain input B ch.4"
		::= { eap3001c01v1Entry 129 }

		-- 1.3.6.1.4.1.10106.3.101291.1.1.131
		eap3001c01v1PhaseAO3I8 OBJECT-TYPE
			SYNTAX Bit0Nor1Inv
			MAX-ACCESS read-write
			STATUS current
			DESCRIPTION
				"Phase input B ch.4"
		::= { eap3001c01v1Entry 131 }

		-- 1.3.6.1.4.1.10106.3.101291.1.1.133
		eap3001c01v1GainAO4I1 OBJECT-TYPE
			SYNTAX Gain24dbMute
			MAX-ACCESS read-write
			STATUS current
			DESCRIPTION
				"Gain input A ch.1"
		::= { eap3001c01v1Entry 133 }

		-- 1.3.6.1.4.1.10106.3.101291.1.1.135
		eap3001c01v1PhaseAO4I1 OBJECT-TYPE
			SYNTAX Bit0Nor1Inv
			MAX-ACCESS read-write
			STATUS current
			DESCRIPTION
				"Phase input A ch.1"
		::= { eap3001c01v1Entry 135 }

		-- 1.3.6.1.4.1.10106.3.101291.1.1.137
		eap3001c01v1GainAO4I2 OBJECT-TYPE
			SYNTAX Gain24dbMute
			MAX-ACCESS read-write
			STATUS current
			DESCRIPTION
				"Gain input A ch.2"
		::= { eap3001c01v1Entry 137 }

		-- 1.3.6.1.4.1.10106.3.101291.1.1.139
		eap3001c01v1PhaseAO4I2 OBJECT-TYPE
			SYNTAX Bit0Nor1Inv
			MAX-ACCESS read-write
			STATUS current
			DESCRIPTION
				"Phase input A ch.2"
		::= { eap3001c01v1Entry 139 }

		-- 1.3.6.1.4.1.10106.3.101291.1.1.141
		eap3001c01v1GainAO4I3 OBJECT-TYPE
			SYNTAX Gain24dbMute
			MAX-ACCESS read-write
			STATUS current
			DESCRIPTION
				"Gain input A ch.3"
		::= { eap3001c01v1Entry 141 }

		-- 1.3.6.1.4.1.10106.3.101291.1.1.143
		eap3001c01v1PhaseAO4I3 OBJECT-TYPE
			SYNTAX Bit0Nor1Inv
			MAX-ACCESS read-write
			STATUS current
			DESCRIPTION
				"Phase input A ch.3"
		::= { eap3001c01v1Entry 143 }

		-- 1.3.6.1.4.1.10106.3.101291.1.1.145
		eap3001c01v1GainAO4I4 OBJECT-TYPE
			SYNTAX Gain24dbMute
			MAX-ACCESS read-write
			STATUS current
			DESCRIPTION
				"Gain input A ch.4"
		::= { eap3001c01v1Entry 145 }

		-- 1.3.6.1.4.1.10106.3.101291.1.1.147
		eap3001c01v1PhaseAO4I4 OBJECT-TYPE
			SYNTAX Bit0Nor1Inv
			MAX-ACCESS read-write
			STATUS current
			DESCRIPTION
				"Phase input A ch.4"
		::= { eap3001c01v1Entry 147 }

		-- 1.3.6.1.4.1.10106.3.101291.1.1.149
		eap3001c01v1GainAO4I5 OBJECT-TYPE
			SYNTAX Gain24dbMute
			MAX-ACCESS read-write
			STATUS current
			DESCRIPTION
				"Gain input B ch.1"
		::= { eap3001c01v1Entry 149 }

		-- 1.3.6.1.4.1.10106.3.101291.1.1.151
		eap3001c01v1PhaseAO4I5 OBJECT-TYPE
			SYNTAX Bit0Nor1Inv
			MAX-ACCESS read-write
			STATUS current
			DESCRIPTION
				"Phase input B ch.1"
		::= { eap3001c01v1Entry 151 }

		-- 1.3.6.1.4.1.10106.3.101291.1.1.153
		eap3001c01v1GainAO4I6 OBJECT-TYPE
			SYNTAX Gain24dbMute
			MAX-ACCESS read-write
			STATUS current
			DESCRIPTION
				"Gain input B ch.2"
		::= { eap3001c01v1Entry 153 }

		-- 1.3.6.1.4.1.10106.3.101291.1.1.155
		eap3001c01v1PhaseAO4I6 OBJECT-TYPE
			SYNTAX Bit0Nor1Inv
			MAX-ACCESS read-write
			STATUS current
			DESCRIPTION
				"Phase input B ch.2"
		::= { eap3001c01v1Entry 155 }

		-- 1.3.6.1.4.1.10106.3.101291.1.1.157
		eap3001c01v1GainAO4I7 OBJECT-TYPE
			SYNTAX Gain24dbMute
			MAX-ACCESS read-write
			STATUS current
			DESCRIPTION
				"Gain input B ch.3"
		::= { eap3001c01v1Entry 157 }

		-- 1.3.6.1.4.1.10106.3.101291.1.1.159
		eap3001c01v1PhaseAO4I7 OBJECT-TYPE
			SYNTAX Bit0Nor1Inv
			MAX-ACCESS read-write
			STATUS current
			DESCRIPTION
				"Phase input B ch.3"
		::= { eap3001c01v1Entry 159 }

		-- 1.3.6.1.4.1.10106.3.101291.1.1.161
		eap3001c01v1GainAO4I8 OBJECT-TYPE
			SYNTAX Gain24dbMute
			MAX-ACCESS read-write
			STATUS current
			DESCRIPTION
				"Gain input B ch.4"
		::= { eap3001c01v1Entry 161 }

		-- 1.3.6.1.4.1.10106.3.101291.1.1.163
		eap3001c01v1PhaseAO4I8 OBJECT-TYPE
			SYNTAX Bit0Nor1Inv
			MAX-ACCESS read-write
			STATUS current
			DESCRIPTION
				"Phase input B ch.4"
		::= { eap3001c01v1Entry 163 }

		-- 1.3.6.1.4.1.10106.3.101291.1.1.165
		eap3001c01v1DelayAO1Msb OBJECT-TYPE
			SYNTAX DelayX256Sampl
			MAX-ACCESS read-write
			STATUS current
			DESCRIPTION
				"Delay coarse"
		::= { eap3001c01v1Entry 165 }

		-- 1.3.6.1.4.1.10106.3.101291.1.1.167
		eap3001c01v1DelayAO1Lsb OBJECT-TYPE
			SYNTAX DelaySamp2
			MAX-ACCESS read-write
			STATUS current
			DESCRIPTION
				"Delay fine"
		::= { eap3001c01v1Entry 167 }

		-- 1.3.6.1.4.1.10106.3.101291.1.1.169
		eap3001c01v1DelayAO2Msb OBJECT-TYPE
			SYNTAX DelayX256Sampl
			MAX-ACCESS read-write
			STATUS current
			DESCRIPTION
				"Delay coarse"
		::= { eap3001c01v1Entry 169 }

		-- 1.3.6.1.4.1.10106.3.101291.1.1.171
		eap3001c01v1DelayAO2Lsb OBJECT-TYPE
			SYNTAX DelaySamp2
			MAX-ACCESS read-write
			STATUS current
			DESCRIPTION
				"Delay fine"
		::= { eap3001c01v1Entry 171 }

		-- 1.3.6.1.4.1.10106.3.101291.1.1.173
		eap3001c01v1DelayAO3Msb OBJECT-TYPE
			SYNTAX DelayX256Sampl
			MAX-ACCESS read-write
			STATUS current
			DESCRIPTION
				"Delay coarse"
		::= { eap3001c01v1Entry 173 }

		-- 1.3.6.1.4.1.10106.3.101291.1.1.175
		eap3001c01v1DelayAO3Lsb OBJECT-TYPE
			SYNTAX DelaySamp2
			MAX-ACCESS read-write
			STATUS current
			DESCRIPTION
				"Delay fine"
		::= { eap3001c01v1Entry 175 }

		-- 1.3.6.1.4.1.10106.3.101291.1.1.177
		eap3001c01v1DelayAO4Msb OBJECT-TYPE
			SYNTAX DelayX256Sampl
			MAX-ACCESS read-write
			STATUS current
			DESCRIPTION
				"Delay coarse"
		::= { eap3001c01v1Entry 177 }

		-- 1.3.6.1.4.1.10106.3.101291.1.1.179
		eap3001c01v1DelayAO4Lsb OBJECT-TYPE
			SYNTAX DelaySamp2
			MAX-ACCESS read-write
			STATUS current
			DESCRIPTION
				"Delay fine"
		::= { eap3001c01v1Entry 179 }

		-- 1.3.6.1.4.1.10106.3.101291.1.1.181
		eap3001c01v1GainBO1I1 OBJECT-TYPE
			SYNTAX Gain24dbMute
			MAX-ACCESS read-write
			STATUS current
			DESCRIPTION
				"Gain input A ch.1"
		::= { eap3001c01v1Entry 181 }

		-- 1.3.6.1.4.1.10106.3.101291.1.1.183
		eap3001c01v1PhaseBO1I1 OBJECT-TYPE
			SYNTAX Bit0Nor1Inv
			MAX-ACCESS read-write
			STATUS current
			DESCRIPTION
				"Phase input A ch.1"
		::= { eap3001c01v1Entry 183 }

		-- 1.3.6.1.4.1.10106.3.101291.1.1.185
		eap3001c01v1GainBO1I2 OBJECT-TYPE
			SYNTAX Gain24dbMute
			MAX-ACCESS read-write
			STATUS current
			DESCRIPTION
				"Gain input A ch.2"
		::= { eap3001c01v1Entry 185 }

		-- 1.3.6.1.4.1.10106.3.101291.1.1.187
		eap3001c01v1PhaseBO1I2 OBJECT-TYPE
			SYNTAX Bit0Nor1Inv
			MAX-ACCESS read-write
			STATUS current
			DESCRIPTION
				"Phase input A ch.2"
		::= { eap3001c01v1Entry 187 }

		-- 1.3.6.1.4.1.10106.3.101291.1.1.189
		eap3001c01v1GainBO1I3 OBJECT-TYPE
			SYNTAX Gain24dbMute
			MAX-ACCESS read-write
			STATUS current
			DESCRIPTION
				"Gain input A ch.3"
		::= { eap3001c01v1Entry 189 }

		-- 1.3.6.1.4.1.10106.3.101291.1.1.191
		eap3001c01v1PhaseBO1I3 OBJECT-TYPE
			SYNTAX Bit0Nor1Inv
			MAX-ACCESS read-write
			STATUS current
			DESCRIPTION
				"Phase input A ch.3"
		::= { eap3001c01v1Entry 191 }

		-- 1.3.6.1.4.1.10106.3.101291.1.1.193
		eap3001c01v1GainBO1I4 OBJECT-TYPE
			SYNTAX Gain24dbMute
			MAX-ACCESS read-write
			STATUS current
			DESCRIPTION
				"Gain input A ch.4"
		::= { eap3001c01v1Entry 193 }

		-- 1.3.6.1.4.1.10106.3.101291.1.1.195
		eap3001c01v1PhaseBO1I4 OBJECT-TYPE
			SYNTAX Bit0Nor1Inv
			MAX-ACCESS read-write
			STATUS current
			DESCRIPTION
				"Phase input A ch.4"
		::= { eap3001c01v1Entry 195 }

		-- 1.3.6.1.4.1.10106.3.101291.1.1.197
		eap3001c01v1GainBO1I5 OBJECT-TYPE
			SYNTAX Gain24dbMute
			MAX-ACCESS read-write
			STATUS current
			DESCRIPTION
				"Gain input B ch.1"
		::= { eap3001c01v1Entry 197 }

		-- 1.3.6.1.4.1.10106.3.101291.1.1.199
		eap3001c01v1PhaseBO1I5 OBJECT-TYPE
			SYNTAX Bit0Nor1Inv
			MAX-ACCESS read-write
			STATUS current
			DESCRIPTION
				"Phase input B ch.1"
		::= { eap3001c01v1Entry 199 }

		-- 1.3.6.1.4.1.10106.3.101291.1.1.201
		eap3001c01v1GainBO1I6 OBJECT-TYPE
			SYNTAX Gain24dbMute
			MAX-ACCESS read-write
			STATUS current
			DESCRIPTION
				"Gain input B ch.2"
		::= { eap3001c01v1Entry 201 }

		-- 1.3.6.1.4.1.10106.3.101291.1.1.203
		eap3001c01v1PhaseBO1I6 OBJECT-TYPE
			SYNTAX Bit0Nor1Inv
			MAX-ACCESS read-write
			STATUS current
			DESCRIPTION
				"Phase input B ch.2"
		::= { eap3001c01v1Entry 203 }

		-- 1.3.6.1.4.1.10106.3.101291.1.1.205
		eap3001c01v1GainBO1I7 OBJECT-TYPE
			SYNTAX Gain24dbMute
			MAX-ACCESS read-write
			STATUS current
			DESCRIPTION
				"Gain input B ch.3"
		::= { eap3001c01v1Entry 205 }

		-- 1.3.6.1.4.1.10106.3.101291.1.1.207
		eap3001c01v1PhaseBO1I7 OBJECT-TYPE
			SYNTAX Bit0Nor1Inv
			MAX-ACCESS read-write
			STATUS current
			DESCRIPTION
				"Phase input B ch.3"
		::= { eap3001c01v1Entry 207 }

		-- 1.3.6.1.4.1.10106.3.101291.1.1.209
		eap3001c01v1GainBO1I8 OBJECT-TYPE
			SYNTAX Gain24dbMute
			MAX-ACCESS read-write
			STATUS current
			DESCRIPTION
				"Gain input B ch.4"
		::= { eap3001c01v1Entry 209 }

		-- 1.3.6.1.4.1.10106.3.101291.1.1.211
		eap3001c01v1PhaseBO1I8 OBJECT-TYPE
			SYNTAX Bit0Nor1Inv
			MAX-ACCESS read-write
			STATUS current
			DESCRIPTION
				"Phase input B ch.4"
		::= { eap3001c01v1Entry 211 }

		-- 1.3.6.1.4.1.10106.3.101291.1.1.213
		eap3001c01v1GainBO2I1 OBJECT-TYPE
			SYNTAX Gain24dbMute
			MAX-ACCESS read-write
			STATUS current
			DESCRIPTION
				"Gain input A ch.1"
		::= { eap3001c01v1Entry 213 }

		-- 1.3.6.1.4.1.10106.3.101291.1.1.215
		eap3001c01v1PhaseBO2I1 OBJECT-TYPE
			SYNTAX Bit0Nor1Inv
			MAX-ACCESS read-write
			STATUS current
			DESCRIPTION
				"Phase input A ch.1"
		::= { eap3001c01v1Entry 215 }

		-- 1.3.6.1.4.1.10106.3.101291.1.1.217
		eap3001c01v1GainBO2I2 OBJECT-TYPE
			SYNTAX Gain24dbMute
			MAX-ACCESS read-write
			STATUS current
			DESCRIPTION
				"Gain input A ch.2"
		::= { eap3001c01v1Entry 217 }

		-- 1.3.6.1.4.1.10106.3.101291.1.1.219
		eap3001c01v1PhaseBO2I2 OBJECT-TYPE
			SYNTAX Bit0Nor1Inv
			MAX-ACCESS read-write
			STATUS current
			DESCRIPTION
				"Phase input A ch.2"
		::= { eap3001c01v1Entry 219 }

		-- 1.3.6.1.4.1.10106.3.101291.1.1.221
		eap3001c01v1GainBO2I3 OBJECT-TYPE
			SYNTAX Gain24dbMute
			MAX-ACCESS read-write
			STATUS current
			DESCRIPTION
				"Gain input A ch.3"
		::= { eap3001c01v1Entry 221 }

		-- 1.3.6.1.4.1.10106.3.101291.1.1.223
		eap3001c01v1PhaseBO2I3 OBJECT-TYPE
			SYNTAX Bit0Nor1Inv
			MAX-ACCESS read-write
			STATUS current
			DESCRIPTION
				"Phase input A ch.3"
		::= { eap3001c01v1Entry 223 }

		-- 1.3.6.1.4.1.10106.3.101291.1.1.225
		eap3001c01v1GainBO2I4 OBJECT-TYPE
			SYNTAX Gain24dbMute
			MAX-ACCESS read-write
			STATUS current
			DESCRIPTION
				"Gain input A ch.4"
		::= { eap3001c01v1Entry 225 }

		-- 1.3.6.1.4.1.10106.3.101291.1.1.227
		eap3001c01v1PhaseBO2I4 OBJECT-TYPE
			SYNTAX Bit0Nor1Inv
			MAX-ACCESS read-write
			STATUS current
			DESCRIPTION
				"Phase input A ch.4"
		::= { eap3001c01v1Entry 227 }

		-- 1.3.6.1.4.1.10106.3.101291.1.1.229
		eap3001c01v1GainBO2I5 OBJECT-TYPE
			SYNTAX Gain24dbMute
			MAX-ACCESS read-write
			STATUS current
			DESCRIPTION
				"Gain input B ch.1"
		::= { eap3001c01v1Entry 229 }

		-- 1.3.6.1.4.1.10106.3.101291.1.1.231
		eap3001c01v1PhaseBO2I5 OBJECT-TYPE
			SYNTAX Bit0Nor1Inv
			MAX-ACCESS read-write
			STATUS current
			DESCRIPTION
				"Phase input B ch.1"
		::= { eap3001c01v1Entry 231 }

		-- 1.3.6.1.4.1.10106.3.101291.1.1.233
		eap3001c01v1GainBO2I6 OBJECT-TYPE
			SYNTAX Gain24dbMute
			MAX-ACCESS read-write
			STATUS current
			DESCRIPTION
				"Gain input B ch.2"
		::= { eap3001c01v1Entry 233 }

		-- 1.3.6.1.4.1.10106.3.101291.1.1.235
		eap3001c01v1PhaseBO2I6 OBJECT-TYPE
			SYNTAX Bit0Nor1Inv
			MAX-ACCESS read-write
			STATUS current
			DESCRIPTION
				"Phase input B ch.2"
		::= { eap3001c01v1Entry 235 }

		-- 1.3.6.1.4.1.10106.3.101291.1.1.237
		eap3001c01v1GainBO2I7 OBJECT-TYPE
			SYNTAX Gain24dbMute
			MAX-ACCESS read-write
			STATUS current
			DESCRIPTION
				"Gain input B ch.3"
		::= { eap3001c01v1Entry 237 }

		-- 1.3.6.1.4.1.10106.3.101291.1.1.239
		eap3001c01v1PhaseBO2I7 OBJECT-TYPE
			SYNTAX Bit0Nor1Inv
			MAX-ACCESS read-write
			STATUS current
			DESCRIPTION
				"Phase input B ch.3"
		::= { eap3001c01v1Entry 239 }

		-- 1.3.6.1.4.1.10106.3.101291.1.1.241
		eap3001c01v1GainBO2I8 OBJECT-TYPE
			SYNTAX Gain24dbMute
			MAX-ACCESS read-write
			STATUS current
			DESCRIPTION
				"Gain input B ch.4"
		::= { eap3001c01v1Entry 241 }

		-- 1.3.6.1.4.1.10106.3.101291.1.1.243
		eap3001c01v1PhaseBO2I8 OBJECT-TYPE
			SYNTAX Bit0Nor1Inv
			MAX-ACCESS read-write
			STATUS current
			DESCRIPTION
				"Phase input B ch.4"
		::= { eap3001c01v1Entry 243 }

		-- 1.3.6.1.4.1.10106.3.101291.1.1.245
		eap3001c01v1GainBO3I1 OBJECT-TYPE
			SYNTAX Gain24dbMute
			MAX-ACCESS read-write
			STATUS current
			DESCRIPTION
				"Gain input A ch.1"
		::= { eap3001c01v1Entry 245 }

		-- 1.3.6.1.4.1.10106.3.101291.1.1.247
		eap3001c01v1PhaseBO3I1 OBJECT-TYPE
			SYNTAX Bit0Nor1Inv
			MAX-ACCESS read-write
			STATUS current
			DESCRIPTION
				"Phase input A ch.1"
		::= { eap3001c01v1Entry 247 }

		-- 1.3.6.1.4.1.10106.3.101291.1.1.249
		eap3001c01v1GainBO3I2 OBJECT-TYPE
			SYNTAX Gain24dbMute
			MAX-ACCESS read-write
			STATUS current
			DESCRIPTION
				"Gain input A ch.2"
		::= { eap3001c01v1Entry 249 }

		-- 1.3.6.1.4.1.10106.3.101291.1.1.251
		eap3001c01v1PhaseBO3I2 OBJECT-TYPE
			SYNTAX Bit0Nor1Inv
			MAX-ACCESS read-write
			STATUS current
			DESCRIPTION
				"Phase input A ch.2"
		::= { eap3001c01v1Entry 251 }

		-- 1.3.6.1.4.1.10106.3.101291.1.1.253
		eap3001c01v1GainBO3I3 OBJECT-TYPE
			SYNTAX Gain24dbMute
			MAX-ACCESS read-write
			STATUS current
			DESCRIPTION
				"Gain input A ch.3"
		::= { eap3001c01v1Entry 253 }

		-- 1.3.6.1.4.1.10106.3.101291.1.1.255
		eap3001c01v1PhaseBO3I3 OBJECT-TYPE
			SYNTAX Bit0Nor1Inv
			MAX-ACCESS read-write
			STATUS current
			DESCRIPTION
				"Phase input A ch.3"
		::= { eap3001c01v1Entry 255 }

		-- 1.3.6.1.4.1.10106.3.101291.1.1.257
		eap3001c01v1GainBO3I4 OBJECT-TYPE
			SYNTAX Gain24dbMute
			MAX-ACCESS read-write
			STATUS current
			DESCRIPTION
				"Gain input A ch.4"
		::= { eap3001c01v1Entry 257 }

		-- 1.3.6.1.4.1.10106.3.101291.1.1.259
		eap3001c01v1PhaseBO3I4 OBJECT-TYPE
			SYNTAX Bit0Nor1Inv
			MAX-ACCESS read-write
			STATUS current
			DESCRIPTION
				"Phase input A ch.4"
		::= { eap3001c01v1Entry 259 }

		-- 1.3.6.1.4.1.10106.3.101291.1.1.261
		eap3001c01v1GainBO3I5 OBJECT-TYPE
			SYNTAX Gain24dbMute
			MAX-ACCESS read-write
			STATUS current
			DESCRIPTION
				"Gain input B ch.1"
		::= { eap3001c01v1Entry 261 }

		-- 1.3.6.1.4.1.10106.3.101291.1.1.263
		eap3001c01v1PhaseBO3I5 OBJECT-TYPE
			SYNTAX Bit0Nor1Inv
			MAX-ACCESS read-write
			STATUS current
			DESCRIPTION
				"Phase input B ch.1"
		::= { eap3001c01v1Entry 263 }

		-- 1.3.6.1.4.1.10106.3.101291.1.1.265
		eap3001c01v1GainBO3I6 OBJECT-TYPE
			SYNTAX Gain24dbMute
			MAX-ACCESS read-write
			STATUS current
			DESCRIPTION
				"Gain input B ch.2"
		::= { eap3001c01v1Entry 265 }

		-- 1.3.6.1.4.1.10106.3.101291.1.1.267
		eap3001c01v1PhaseBO3I6 OBJECT-TYPE
			SYNTAX Bit0Nor1Inv
			MAX-ACCESS read-write
			STATUS current
			DESCRIPTION
				"Phase input B ch.2"
		::= { eap3001c01v1Entry 267 }

		-- 1.3.6.1.4.1.10106.3.101291.1.1.269
		eap3001c01v1GainBO3I7 OBJECT-TYPE
			SYNTAX Gain24dbMute
			MAX-ACCESS read-write
			STATUS current
			DESCRIPTION
				"Gain input B ch.3"
		::= { eap3001c01v1Entry 269 }

		-- 1.3.6.1.4.1.10106.3.101291.1.1.271
		eap3001c01v1PhaseBO3I7 OBJECT-TYPE
			SYNTAX Bit0Nor1Inv
			MAX-ACCESS read-write
			STATUS current
			DESCRIPTION
				"Phase input B ch.3"
		::= { eap3001c01v1Entry 271 }

		-- 1.3.6.1.4.1.10106.3.101291.1.1.273
		eap3001c01v1GainBO3I8 OBJECT-TYPE
			SYNTAX Gain24dbMute
			MAX-ACCESS read-write
			STATUS current
			DESCRIPTION
				"Gain input B ch.4"
		::= { eap3001c01v1Entry 273 }

		-- 1.3.6.1.4.1.10106.3.101291.1.1.275
		eap3001c01v1PhaseBO3I8 OBJECT-TYPE
			SYNTAX Bit0Nor1Inv
			MAX-ACCESS read-write
			STATUS current
			DESCRIPTION
				"Phase input B ch.4"
		::= { eap3001c01v1Entry 275 }

		-- 1.3.6.1.4.1.10106.3.101291.1.1.277
		eap3001c01v1GainBO4I1 OBJECT-TYPE
			SYNTAX Gain24dbMute
			MAX-ACCESS read-write
			STATUS current
			DESCRIPTION
				"Gain input A ch.1"
		::= { eap3001c01v1Entry 277 }

		-- 1.3.6.1.4.1.10106.3.101291.1.1.279
		eap3001c01v1PhaseBO4I1 OBJECT-TYPE
			SYNTAX Bit0Nor1Inv
			MAX-ACCESS read-write
			STATUS current
			DESCRIPTION
				"Phase input A ch.1"
		::= { eap3001c01v1Entry 279 }

		-- 1.3.6.1.4.1.10106.3.101291.1.1.281
		eap3001c01v1GainBO4I2 OBJECT-TYPE
			SYNTAX Gain24dbMute
			MAX-ACCESS read-write
			STATUS current
			DESCRIPTION
				"Gain input A ch.2"
		::= { eap3001c01v1Entry 281 }

		-- 1.3.6.1.4.1.10106.3.101291.1.1.283
		eap3001c01v1PhaseBO4I2 OBJECT-TYPE
			SYNTAX Bit0Nor1Inv
			MAX-ACCESS read-write
			STATUS current
			DESCRIPTION
				"Phase input A ch.2"
		::= { eap3001c01v1Entry 283 }

		-- 1.3.6.1.4.1.10106.3.101291.1.1.285
		eap3001c01v1GainBO4I3 OBJECT-TYPE
			SYNTAX Gain24dbMute
			MAX-ACCESS read-write
			STATUS current
			DESCRIPTION
				"Gain input A ch.3"
		::= { eap3001c01v1Entry 285 }

		-- 1.3.6.1.4.1.10106.3.101291.1.1.287
		eap3001c01v1PhaseBO4I3 OBJECT-TYPE
			SYNTAX Bit0Nor1Inv
			MAX-ACCESS read-write
			STATUS current
			DESCRIPTION
				"Phase input A ch.3"
		::= { eap3001c01v1Entry 287 }

		-- 1.3.6.1.4.1.10106.3.101291.1.1.289
		eap3001c01v1GainBO4I4 OBJECT-TYPE
			SYNTAX Gain24dbMute
			MAX-ACCESS read-write
			STATUS current
			DESCRIPTION
				"Gain input A ch.4"
		::= { eap3001c01v1Entry 289 }

		-- 1.3.6.1.4.1.10106.3.101291.1.1.291
		eap3001c01v1PhaseBO4I4 OBJECT-TYPE
			SYNTAX Bit0Nor1Inv
			MAX-ACCESS read-write
			STATUS current
			DESCRIPTION
				"Phase input A ch.4"
		::= { eap3001c01v1Entry 291 }

		-- 1.3.6.1.4.1.10106.3.101291.1.1.293
		eap3001c01v1GainBO4I5 OBJECT-TYPE
			SYNTAX Gain24dbMute
			MAX-ACCESS read-write
			STATUS current
			DESCRIPTION
				"Gain input B ch.1"
		::= { eap3001c01v1Entry 293 }

		-- 1.3.6.1.4.1.10106.3.101291.1.1.295
		eap3001c01v1PhaseBO4I5 OBJECT-TYPE
			SYNTAX Bit0Nor1Inv
			MAX-ACCESS read-write
			STATUS current
			DESCRIPTION
				"Phase input B ch.1"
		::= { eap3001c01v1Entry 295 }

		-- 1.3.6.1.4.1.10106.3.101291.1.1.297
		eap3001c01v1GainBO4I6 OBJECT-TYPE
			SYNTAX Gain24dbMute
			MAX-ACCESS read-write
			STATUS current
			DESCRIPTION
				"Gain input B ch.2"
		::= { eap3001c01v1Entry 297 }

		-- 1.3.6.1.4.1.10106.3.101291.1.1.299
		eap3001c01v1PhaseBO4I6 OBJECT-TYPE
			SYNTAX Bit0Nor1Inv
			MAX-ACCESS read-write
			STATUS current
			DESCRIPTION
				"Phase input B ch.2"
		::= { eap3001c01v1Entry 299 }

		-- 1.3.6.1.4.1.10106.3.101291.1.1.301
		eap3001c01v1GainBO4I7 OBJECT-TYPE
			SYNTAX Gain24dbMute
			MAX-ACCESS read-write
			STATUS current
			DESCRIPTION
				"Gain input B ch.3"
		::= { eap3001c01v1Entry 301 }

		-- 1.3.6.1.4.1.10106.3.101291.1.1.303
		eap3001c01v1PhaseBO4I7 OBJECT-TYPE
			SYNTAX Bit0Nor1Inv
			MAX-ACCESS read-write
			STATUS current
			DESCRIPTION
				"Phase input B ch.3"
		::= { eap3001c01v1Entry 303 }

		-- 1.3.6.1.4.1.10106.3.101291.1.1.305
		eap3001c01v1GainBO4I8 OBJECT-TYPE
			SYNTAX Gain24dbMute
			MAX-ACCESS read-write
			STATUS current
			DESCRIPTION
				"Gain input B ch.4"
		::= { eap3001c01v1Entry 305 }

		-- 1.3.6.1.4.1.10106.3.101291.1.1.307
		eap3001c01v1PhaseBO4I8 OBJECT-TYPE
			SYNTAX Bit0Nor1Inv
			MAX-ACCESS read-write
			STATUS current
			DESCRIPTION
				"Phase input B ch.4"
		::= { eap3001c01v1Entry 307 }

		-- 1.3.6.1.4.1.10106.3.101291.1.1.309
		eap3001c01v1DelayBO1Msb OBJECT-TYPE
			SYNTAX DelayX256Sampl
			MAX-ACCESS read-write
			STATUS current
			DESCRIPTION
				"Delay coarse"
		::= { eap3001c01v1Entry 309 }

		-- 1.3.6.1.4.1.10106.3.101291.1.1.311
		eap3001c01v1DelayBO1Lsb OBJECT-TYPE
			SYNTAX DelaySamp2
			MAX-ACCESS read-write
			STATUS current
			DESCRIPTION
				"Delay fine"
		::= { eap3001c01v1Entry 311 }

		-- 1.3.6.1.4.1.10106.3.101291.1.1.313
		eap3001c01v1DelayBO2Msb OBJECT-TYPE
			SYNTAX DelayX256Sampl
			MAX-ACCESS read-write
			STATUS current
			DESCRIPTION
				"Delay coarse"
		::= { eap3001c01v1Entry 313 }

		-- 1.3.6.1.4.1.10106.3.101291.1.1.315
		eap3001c01v1DelayBO2Lsb OBJECT-TYPE
			SYNTAX DelaySamp2
			MAX-ACCESS read-write
			STATUS current
			DESCRIPTION
				"Delay fine"
		::= { eap3001c01v1Entry 315 }

		-- 1.3.6.1.4.1.10106.3.101291.1.1.317
		eap3001c01v1DelayBO3Msb OBJECT-TYPE
			SYNTAX DelayX256Sampl
			MAX-ACCESS read-write
			STATUS current
			DESCRIPTION
				"Delay coarse"
		::= { eap3001c01v1Entry 317 }

		-- 1.3.6.1.4.1.10106.3.101291.1.1.319
		eap3001c01v1DelayBO3Lsb OBJECT-TYPE
			SYNTAX DelaySamp2
			MAX-ACCESS read-write
			STATUS current
			DESCRIPTION
				"Delay fine"
		::= { eap3001c01v1Entry 319 }

		-- 1.3.6.1.4.1.10106.3.101291.1.1.321
		eap3001c01v1DelayBO4Msb OBJECT-TYPE
			SYNTAX DelayX256Sampl
			MAX-ACCESS read-write
			STATUS current
			DESCRIPTION
				"Delay coarse"
		::= { eap3001c01v1Entry 321 }

		-- 1.3.6.1.4.1.10106.3.101291.1.1.323
		eap3001c01v1DelayBO4Lsb OBJECT-TYPE
			SYNTAX DelaySamp2
			MAX-ACCESS read-write
			STATUS current
			DESCRIPTION
				"Delay fine"
		::= { eap3001c01v1Entry 323 }

		-- 1.3.6.1.4.1.10106.3.101291.1.1.325
		eap3001c01v1NoSigA OBJECT-TYPE
			SYNTAX BitFail
			MAX-ACCESS read-only
			STATUS current
			DESCRIPTION
				"SDI input signal status"
		::= { eap3001c01v1Entry 325 }

		-- 1.3.6.1.4.1.10106.3.101291.1.1.326
		eap3001c01v1NoSigATrapEnable OBJECT-TYPE
			SYNTAX AlarmEnable
			MAX-ACCESS read-write
			STATUS current
			DESCRIPTION
				"SDI input signal status Trap Enable"
		::= { eap3001c01v1Entry 326 }

		-- 1.3.6.1.4.1.10106.3.101291.1.1.327
		eap3001c01v1EdhErrA OBJECT-TYPE
			SYNTAX BitFail
			MAX-ACCESS read-only
			STATUS current
			DESCRIPTION
				"Indicates EDH errors"
		::= { eap3001c01v1Entry 327 }

		-- 1.3.6.1.4.1.10106.3.101291.1.1.329
		eap3001c01v1AudioFr0ErrA OBJECT-TYPE
			SYNTAX BitFail
			MAX-ACCESS read-only
			STATUS current
			DESCRIPTION
				"Indicates that there is no valid audio in the frame 0"
		::= { eap3001c01v1Entry 329 }

		-- 1.3.6.1.4.1.10106.3.101291.1.1.330
		eap3001c01v1AudioFr0ErrATrapEnable OBJECT-TYPE
			SYNTAX AlarmEnable
			MAX-ACCESS read-write
			STATUS current
			DESCRIPTION
				"Indicates that there is no valid audio in the frame 0 Trap Enable"
		::= { eap3001c01v1Entry 330 }

		-- 1.3.6.1.4.1.10106.3.101291.1.1.331
		eap3001c01v1AudioFr1ErrA OBJECT-TYPE
			SYNTAX BitFail
			MAX-ACCESS read-only
			STATUS current
			DESCRIPTION
				"Indicates that there is no valid audio in the frame 1"
		::= { eap3001c01v1Entry 331 }

		-- 1.3.6.1.4.1.10106.3.101291.1.1.332
		eap3001c01v1AudioFr1ErrATrapEnable OBJECT-TYPE
			SYNTAX AlarmEnable
			MAX-ACCESS read-write
			STATUS current
			DESCRIPTION
				"Indicates that there is no valid audio in the frame 1 Trap Enable"
		::= { eap3001c01v1Entry 332 }

		-- 1.3.6.1.4.1.10106.3.101291.1.1.333
		eap3001c01v1AudioGr1A OBJECT-TYPE
			SYNTAX Bit0No1Yes
			MAX-ACCESS read-only
			STATUS current
			DESCRIPTION
				"Indicates the presence of packets of audio group 1"
		::= { eap3001c01v1Entry 333 }

		-- 1.3.6.1.4.1.10106.3.101291.1.1.335
		eap3001c01v1AudioGr2A OBJECT-TYPE
			SYNTAX Bit0No1Yes
			MAX-ACCESS read-only
			STATUS current
			DESCRIPTION
				"Indicates the presence of packets of audio group 2"
		::= { eap3001c01v1Entry 335 }

		-- 1.3.6.1.4.1.10106.3.101291.1.1.337
		eap3001c01v1AudioGr3A OBJECT-TYPE
			SYNTAX Bit0No1Yes
			MAX-ACCESS read-only
			STATUS current
			DESCRIPTION
				"Indicates the presence of packets of audio group 3"
		::= { eap3001c01v1Entry 337 }

		-- 1.3.6.1.4.1.10106.3.101291.1.1.339
		eap3001c01v1AudioGr4A OBJECT-TYPE
			SYNTAX Bit0No1Yes
			MAX-ACCESS read-only
			STATUS current
			DESCRIPTION
				"Indicates the presence of packets of audio group 4"
		::= { eap3001c01v1Entry 339 }

		-- 1.3.6.1.4.1.10106.3.101291.1.1.341
		eap3001c01v1NoSigB OBJECT-TYPE
			SYNTAX BitFail
			MAX-ACCESS read-only
			STATUS current
			DESCRIPTION
				"SDI input signal status"
		::= { eap3001c01v1Entry 341 }

		-- 1.3.6.1.4.1.10106.3.101291.1.1.342
		eap3001c01v1NoSigBTrapEnable OBJECT-TYPE
			SYNTAX AlarmEnable
			MAX-ACCESS read-write
			STATUS current
			DESCRIPTION
				"SDI input signal status Trap Enable"
		::= { eap3001c01v1Entry 342 }

		-- 1.3.6.1.4.1.10106.3.101291.1.1.343
		eap3001c01v1EdhErrB OBJECT-TYPE
			SYNTAX BitFail
			MAX-ACCESS read-only
			STATUS current
			DESCRIPTION
				"Indicates EDH errors"
		::= { eap3001c01v1Entry 343 }

		-- 1.3.6.1.4.1.10106.3.101291.1.1.345
		eap3001c01v1AudioFr0ErrB OBJECT-TYPE
			SYNTAX BitFail
			MAX-ACCESS read-only
			STATUS current
			DESCRIPTION
				"Indicates that there is no valid audio in the frame 0"
		::= { eap3001c01v1Entry 345 }

		-- 1.3.6.1.4.1.10106.3.101291.1.1.346
		eap3001c01v1AudioFr0ErrBTrapEnable OBJECT-TYPE
			SYNTAX AlarmEnable
			MAX-ACCESS read-write
			STATUS current
			DESCRIPTION
				"Indicates that there is no valid audio in the frame 0 Trap Enable"
		::= { eap3001c01v1Entry 346 }

		-- 1.3.6.1.4.1.10106.3.101291.1.1.347
		eap3001c01v1AudioFr1ErrB OBJECT-TYPE
			SYNTAX BitFail
			MAX-ACCESS read-only
			STATUS current
			DESCRIPTION
				"Indicates that there is no valid audio in the frame 1"
		::= { eap3001c01v1Entry 347 }

		-- 1.3.6.1.4.1.10106.3.101291.1.1.348
		eap3001c01v1AudioFr1ErrBTrapEnable OBJECT-TYPE
			SYNTAX AlarmEnable
			MAX-ACCESS read-write
			STATUS current
			DESCRIPTION
				"Indicates that there is no valid audio in the frame 1 Trap Enable"
		::= { eap3001c01v1Entry 348 }

		-- 1.3.6.1.4.1.10106.3.101291.1.1.349
		eap3001c01v1AudioGr1B OBJECT-TYPE
			SYNTAX Bit0No1Yes
			MAX-ACCESS read-only
			STATUS current
			DESCRIPTION
				"Indicates the presence of packets of audio group 1"
		::= { eap3001c01v1Entry 349 }

		-- 1.3.6.1.4.1.10106.3.101291.1.1.351
		eap3001c01v1AudioGr2B OBJECT-TYPE
			SYNTAX Bit0No1Yes
			MAX-ACCESS read-only
			STATUS current
			DESCRIPTION
				"Indicates the presence of packets of audio group 2"
		::= { eap3001c01v1Entry 351 }

		-- 1.3.6.1.4.1.10106.3.101291.1.1.353
		eap3001c01v1AudioGr3B OBJECT-TYPE
			SYNTAX Bit0No1Yes
			MAX-ACCESS read-only
			STATUS current
			DESCRIPTION
				"Indicates the presence of packets of audio group 3"
		::= { eap3001c01v1Entry 353 }

		-- 1.3.6.1.4.1.10106.3.101291.1.1.355
		eap3001c01v1AudioGr4B OBJECT-TYPE
			SYNTAX Bit0No1Yes
			MAX-ACCESS read-only
			STATUS current
			DESCRIPTION
				"Indicates the presence of packets of audio group 4"
		::= { eap3001c01v1Entry 355 }

		-- 1.3.6.1.4.1.10106.3.272801
		ur-3100r05v1 OBJECT IDENTIFIER ::= { albalaProducts 272801 }

		-- 1.3.6.1.4.1.10106.3.272801.1
		ur-3100r05v1Table  OBJECT-TYPE
			SYNTAX SEQUENCE OF Ur-3100r05v1Entry
			MAX-ACCESS not-accessible
			STATUS current
			DESCRIPTION
				"Module  UR-3100R05V1 Table"
			::= { ur-3100r05v1 1 }

		-- 1.3.6.1.4.1.10106.3.272801.1.1
		ur-3100r05v1Entry  OBJECT-TYPE
			SYNTAX Ur-3100r05v1Entry
			MAX-ACCESS not-accessible
			STATUS current
			DESCRIPTION
				"Module UR-3100R05V1 Entry"
			INDEX { ur-3100r05v1Index }
			::= { ur-3100r05v1Table 1 }

			Ur-3100r05v1Entry ::=
			SEQUENCE {
				ur-3100r05v1Index
				ModuleIndex,
				ur-3100r05v1PwrFailR
				BitFail,
				ur-3100r05v1PwrFailRTrapEnable
				AlarmEnable,
				ur-3100r05v1PwrFailL
				BitFail,
				ur-3100r05v1PwrFailLTrapEnable
				AlarmEnable,
				ur-3100r05v1VccVoltage
				VccVoltage,
				ur-3100r05v1SerialNo
				SerialNo
			 }

		-- 1.3.6.1.4.1.10106.3.101291.1.1.1
		ur-3100r05v1Index OBJECT-TYPE
			SYNTAX ModuleIndex
			MAX-ACCESS read-only
			STATUS current
			DESCRIPTION
				"Index of UR-3100R05V1 Table"
		::= { ur-3100r05v1Entry 1 }

		-- 1.3.6.1.4.1.10106.3.101291.1.1.3
		ur-3100r05v1PwrFailR OBJECT-TYPE
			SYNTAX BitFail
			MAX-ACCESS read-only
			STATUS current
			DESCRIPTION
				"Indicates the rigth power supply status"
		::= { ur-3100r05v1Entry 3 }

		-- 1.3.6.1.4.1.10106.3.101291.1.1.4
		ur-3100r05v1PwrFailRTrapEnable OBJECT-TYPE
			SYNTAX AlarmEnable
			MAX-ACCESS read-write
			STATUS current
			DESCRIPTION
				"Indicates the rigth power supply status Trap Enable"
		::= { ur-3100r05v1Entry 4 }

		-- 1.3.6.1.4.1.10106.3.101291.1.1.5
		ur-3100r05v1PwrFailL OBJECT-TYPE
			SYNTAX BitFail
			MAX-ACCESS read-only
			STATUS current
			DESCRIPTION
				"Indicates the left power supply status"
		::= { ur-3100r05v1Entry 5 }

		-- 1.3.6.1.4.1.10106.3.101291.1.1.6
		ur-3100r05v1PwrFailLTrapEnable OBJECT-TYPE
			SYNTAX AlarmEnable
			MAX-ACCESS read-write
			STATUS current
			DESCRIPTION
				"Indicates the left power supply status Trap Enable"
		::= { ur-3100r05v1Entry 6 }

		-- 1.3.6.1.4.1.10106.3.101291.1.1.7
		ur-3100r05v1VccVoltage OBJECT-TYPE
			SYNTAX VccVoltage
			MAX-ACCESS read-only
			STATUS current
			DESCRIPTION
				"Indicates the uC voltage"
		::= { ur-3100r05v1Entry 7 }

		-- 1.3.6.1.4.1.10106.3.101291.1.1.9
		ur-3100r05v1SerialNo OBJECT-TYPE
			SYNTAX SerialNo
			MAX-ACCESS read-only
			STATUS current
			DESCRIPTION
				"Serial number"
		::= { ur-3100r05v1Entry 9 }

		-- 1.3.6.1.4.1.10106.3.272901
		ur-3100r06v1 OBJECT IDENTIFIER ::= { albalaProducts 272901 }

		-- 1.3.6.1.4.1.10106.3.272901.1
		ur-3100r06v1Table  OBJECT-TYPE
			SYNTAX SEQUENCE OF Ur-3100r06v1Entry
			MAX-ACCESS not-accessible
			STATUS current
			DESCRIPTION
				"Module  UR-3100R06V1 Table"
			::= { ur-3100r06v1 1 }

		-- 1.3.6.1.4.1.10106.3.272901.1.1
		ur-3100r06v1Entry  OBJECT-TYPE
			SYNTAX Ur-3100r06v1Entry
			MAX-ACCESS not-accessible
			STATUS current
			DESCRIPTION
				"Module UR-3100R06V1 Entry"
			INDEX { ur-3100r06v1Index }
			::= { ur-3100r06v1Table 1 }

			Ur-3100r06v1Entry ::=
			SEQUENCE {
				ur-3100r06v1Index
				ModuleIndex,
				ur-3100r06v1PwrFailR
				BitFail,
				ur-3100r06v1PwrFailRTrapEnable
				AlarmEnable,
				ur-3100r06v1PwrFailL
				BitFail,
				ur-3100r06v1PwrFailLTrapEnable
				AlarmEnable,
				ur-3100r06v1VccVoltage
				VccVoltage,
				ur-3100r06v1SerialNo
				SerialNo
			 }

		-- 1.3.6.1.4.1.10106.3.101291.1.1.1
		ur-3100r06v1Index OBJECT-TYPE
			SYNTAX ModuleIndex
			MAX-ACCESS read-only
			STATUS current
			DESCRIPTION
				"Index of UR-3100R06V1 Table"
		::= { ur-3100r06v1Entry 1 }

		-- 1.3.6.1.4.1.10106.3.101291.1.1.3
		ur-3100r06v1PwrFailR OBJECT-TYPE
			SYNTAX BitFail
			MAX-ACCESS read-only
			STATUS current
			DESCRIPTION
				"Indicates the rigth power supply status"
		::= { ur-3100r06v1Entry 3 }

		-- 1.3.6.1.4.1.10106.3.101291.1.1.4
		ur-3100r06v1PwrFailRTrapEnable OBJECT-TYPE
			SYNTAX AlarmEnable
			MAX-ACCESS read-write
			STATUS current
			DESCRIPTION
				"Indicates the rigth power supply status Trap Enable"
		::= { ur-3100r06v1Entry 4 }

		-- 1.3.6.1.4.1.10106.3.101291.1.1.5
		ur-3100r06v1PwrFailL OBJECT-TYPE
			SYNTAX BitFail
			MAX-ACCESS read-only
			STATUS current
			DESCRIPTION
				"Indicates the left power supply status"
		::= { ur-3100r06v1Entry 5 }

		-- 1.3.6.1.4.1.10106.3.101291.1.1.6
		ur-3100r06v1PwrFailLTrapEnable OBJECT-TYPE
			SYNTAX AlarmEnable
			MAX-ACCESS read-write
			STATUS current
			DESCRIPTION
				"Indicates the left power supply status Trap Enable"
		::= { ur-3100r06v1Entry 6 }

		-- 1.3.6.1.4.1.10106.3.101291.1.1.7
		ur-3100r06v1VccVoltage OBJECT-TYPE
			SYNTAX VccVoltage
			MAX-ACCESS read-only
			STATUS current
			DESCRIPTION
				"Indicates the uC voltage"
		::= { ur-3100r06v1Entry 7 }

		-- 1.3.6.1.4.1.10106.3.101291.1.1.9
		ur-3100r06v1SerialNo OBJECT-TYPE
			SYNTAX SerialNo
			MAX-ACCESS read-only
			STATUS current
			DESCRIPTION
				"Serial number"
		::= { ur-3100r06v1Entry 9 }

		-- 1.3.6.1.4.1.10106.3.273001
		ur-3100r07v1 OBJECT IDENTIFIER ::= { albalaProducts 273001 }

		-- 1.3.6.1.4.1.10106.3.273001.1
		ur-3100r07v1Table  OBJECT-TYPE
			SYNTAX SEQUENCE OF Ur-3100r07v1Entry
			MAX-ACCESS not-accessible
			STATUS current
			DESCRIPTION
				"Module  UR-3100R07V1 Table"
			::= { ur-3100r07v1 1 }

		-- 1.3.6.1.4.1.10106.3.273001.1.1
		ur-3100r07v1Entry  OBJECT-TYPE
			SYNTAX Ur-3100r07v1Entry
			MAX-ACCESS not-accessible
			STATUS current
			DESCRIPTION
				"Module UR-3100R07V1 Entry"
			INDEX { ur-3100r07v1Index }
			::= { ur-3100r07v1Table 1 }

			Ur-3100r07v1Entry ::=
			SEQUENCE {
				ur-3100r07v1Index
				ModuleIndex,
				ur-3100r07v1PwrFailR
				BitFail,
				ur-3100r07v1PwrFailRTrapEnable
				AlarmEnable,
				ur-3100r07v1PwrFailL
				BitFail,
				ur-3100r07v1PwrFailLTrapEnable
				AlarmEnable,
				ur-3100r07v1VccVoltage
				VccVoltage,
				ur-3100r07v1SerialNo
				SerialNo
			 }

		-- 1.3.6.1.4.1.10106.3.101291.1.1.1
		ur-3100r07v1Index OBJECT-TYPE
			SYNTAX ModuleIndex
			MAX-ACCESS read-only
			STATUS current
			DESCRIPTION
				"Index of UR-3100R07V1 Table"
		::= { ur-3100r07v1Entry 1 }

		-- 1.3.6.1.4.1.10106.3.101291.1.1.3
		ur-3100r07v1PwrFailR OBJECT-TYPE
			SYNTAX BitFail
			MAX-ACCESS read-only
			STATUS current
			DESCRIPTION
				"Indicates the rigth power supply status"
		::= { ur-3100r07v1Entry 3 }

		-- 1.3.6.1.4.1.10106.3.101291.1.1.4
		ur-3100r07v1PwrFailRTrapEnable OBJECT-TYPE
			SYNTAX AlarmEnable
			MAX-ACCESS read-write
			STATUS current
			DESCRIPTION
				"Indicates the rigth power supply status Trap Enable"
		::= { ur-3100r07v1Entry 4 }

		-- 1.3.6.1.4.1.10106.3.101291.1.1.5
		ur-3100r07v1PwrFailL OBJECT-TYPE
			SYNTAX BitFail
			MAX-ACCESS read-only
			STATUS current
			DESCRIPTION
				"Indicates the left power supply status"
		::= { ur-3100r07v1Entry 5 }

		-- 1.3.6.1.4.1.10106.3.101291.1.1.6
		ur-3100r07v1PwrFailLTrapEnable OBJECT-TYPE
			SYNTAX AlarmEnable
			MAX-ACCESS read-write
			STATUS current
			DESCRIPTION
				"Indicates the left power supply status Trap Enable"
		::= { ur-3100r07v1Entry 6 }

		-- 1.3.6.1.4.1.10106.3.101291.1.1.7
		ur-3100r07v1VccVoltage OBJECT-TYPE
			SYNTAX VccVoltage
			MAX-ACCESS read-only
			STATUS current
			DESCRIPTION
				"Indicates the uC voltage"
		::= { ur-3100r07v1Entry 7 }

		-- 1.3.6.1.4.1.10106.3.101291.1.1.9
		ur-3100r07v1SerialNo OBJECT-TYPE
			SYNTAX SerialNo
			MAX-ACCESS read-only
			STATUS current
			DESCRIPTION
				"Serial number"
		::= { ur-3100r07v1Entry 9 }

		-- 1.3.6.1.4.1.10106.3.273101
		ur-3100r08v1 OBJECT IDENTIFIER ::= { albalaProducts 273101 }

		-- 1.3.6.1.4.1.10106.3.273101.1
		ur-3100r08v1Table  OBJECT-TYPE
			SYNTAX SEQUENCE OF Ur-3100r08v1Entry
			MAX-ACCESS not-accessible
			STATUS current
			DESCRIPTION
				"Module  UR-3100R08V1 Table"
			::= { ur-3100r08v1 1 }

		-- 1.3.6.1.4.1.10106.3.273101.1.1
		ur-3100r08v1Entry  OBJECT-TYPE
			SYNTAX Ur-3100r08v1Entry
			MAX-ACCESS not-accessible
			STATUS current
			DESCRIPTION
				"Module UR-3100R08V1 Entry"
			INDEX { ur-3100r08v1Index }
			::= { ur-3100r08v1Table 1 }

			Ur-3100r08v1Entry ::=
			SEQUENCE {
				ur-3100r08v1Index
				ModuleIndex,
				ur-3100r08v1PwrFailR
				BitFail,
				ur-3100r08v1PwrFailRTrapEnable
				AlarmEnable,
				ur-3100r08v1PwrFailL
				BitFail,
				ur-3100r08v1PwrFailLTrapEnable
				AlarmEnable,
				ur-3100r08v1VccVoltage
				VccVoltage,
				ur-3100r08v1SerialNo
				SerialNo
			 }

		-- 1.3.6.1.4.1.10106.3.101291.1.1.1
		ur-3100r08v1Index OBJECT-TYPE
			SYNTAX ModuleIndex
			MAX-ACCESS read-only
			STATUS current
			DESCRIPTION
				"Index of UR-3100R08V1 Table"
		::= { ur-3100r08v1Entry 1 }

		-- 1.3.6.1.4.1.10106.3.101291.1.1.3
		ur-3100r08v1PwrFailR OBJECT-TYPE
			SYNTAX BitFail
			MAX-ACCESS read-only
			STATUS current
			DESCRIPTION
				"Indicates the rigth power supply status"
		::= { ur-3100r08v1Entry 3 }

		-- 1.3.6.1.4.1.10106.3.101291.1.1.4
		ur-3100r08v1PwrFailRTrapEnable OBJECT-TYPE
			SYNTAX AlarmEnable
			MAX-ACCESS read-write
			STATUS current
			DESCRIPTION
				"Indicates the rigth power supply status Trap Enable"
		::= { ur-3100r08v1Entry 4 }

		-- 1.3.6.1.4.1.10106.3.101291.1.1.5
		ur-3100r08v1PwrFailL OBJECT-TYPE
			SYNTAX BitFail
			MAX-ACCESS read-only
			STATUS current
			DESCRIPTION
				"Indicates the left power supply status"
		::= { ur-3100r08v1Entry 5 }

		-- 1.3.6.1.4.1.10106.3.101291.1.1.6
		ur-3100r08v1PwrFailLTrapEnable OBJECT-TYPE
			SYNTAX AlarmEnable
			MAX-ACCESS read-write
			STATUS current
			DESCRIPTION
				"Indicates the left power supply status Trap Enable"
		::= { ur-3100r08v1Entry 6 }

		-- 1.3.6.1.4.1.10106.3.101291.1.1.7
		ur-3100r08v1VccVoltage OBJECT-TYPE
			SYNTAX VccVoltage
			MAX-ACCESS read-only
			STATUS current
			DESCRIPTION
				"Indicates the uC voltage"
		::= { ur-3100r08v1Entry 7 }

		-- 1.3.6.1.4.1.10106.3.101291.1.1.9
		ur-3100r08v1SerialNo OBJECT-TYPE
			SYNTAX SerialNo
			MAX-ACCESS read-only
			STATUS current
			DESCRIPTION
				"Serial number"
		::= { ur-3100r08v1Entry 9 }

		-- 1.3.6.1.4.1.10106.3.273201
		ur-3100r09v1 OBJECT IDENTIFIER ::= { albalaProducts 273201 }

		-- 1.3.6.1.4.1.10106.3.273201.1
		ur-3100r09v1Table  OBJECT-TYPE
			SYNTAX SEQUENCE OF Ur-3100r09v1Entry
			MAX-ACCESS not-accessible
			STATUS current
			DESCRIPTION
				"Module  UR-3100R09V1 Table"
			::= { ur-3100r09v1 1 }

		-- 1.3.6.1.4.1.10106.3.273201.1.1
		ur-3100r09v1Entry  OBJECT-TYPE
			SYNTAX Ur-3100r09v1Entry
			MAX-ACCESS not-accessible
			STATUS current
			DESCRIPTION
				"Module UR-3100R09V1 Entry"
			INDEX { ur-3100r09v1Index }
			::= { ur-3100r09v1Table 1 }

			Ur-3100r09v1Entry ::=
			SEQUENCE {
				ur-3100r09v1Index
				ModuleIndex,
				ur-3100r09v1PwrFailR
				BitFail,
				ur-3100r09v1PwrFailRTrapEnable
				AlarmEnable,
				ur-3100r09v1PwrFailL
				BitFail,
				ur-3100r09v1PwrFailLTrapEnable
				AlarmEnable,
				ur-3100r09v1VccVoltage
				VccVoltage,
				ur-3100r09v1SerialNo
				SerialNo
			 }

		-- 1.3.6.1.4.1.10106.3.101291.1.1.1
		ur-3100r09v1Index OBJECT-TYPE
			SYNTAX ModuleIndex
			MAX-ACCESS read-only
			STATUS current
			DESCRIPTION
				"Index of UR-3100R09V1 Table"
		::= { ur-3100r09v1Entry 1 }

		-- 1.3.6.1.4.1.10106.3.101291.1.1.3
		ur-3100r09v1PwrFailR OBJECT-TYPE
			SYNTAX BitFail
			MAX-ACCESS read-only
			STATUS current
			DESCRIPTION
				"Indicates the rigth power supply status"
		::= { ur-3100r09v1Entry 3 }

		-- 1.3.6.1.4.1.10106.3.101291.1.1.4
		ur-3100r09v1PwrFailRTrapEnable OBJECT-TYPE
			SYNTAX AlarmEnable
			MAX-ACCESS read-write
			STATUS current
			DESCRIPTION
				"Indicates the rigth power supply status Trap Enable"
		::= { ur-3100r09v1Entry 4 }

		-- 1.3.6.1.4.1.10106.3.101291.1.1.5
		ur-3100r09v1PwrFailL OBJECT-TYPE
			SYNTAX BitFail
			MAX-ACCESS read-only
			STATUS current
			DESCRIPTION
				"Indicates the left power supply status"
		::= { ur-3100r09v1Entry 5 }

		-- 1.3.6.1.4.1.10106.3.101291.1.1.6
		ur-3100r09v1PwrFailLTrapEnable OBJECT-TYPE
			SYNTAX AlarmEnable
			MAX-ACCESS read-write
			STATUS current
			DESCRIPTION
				"Indicates the left power supply status Trap Enable"
		::= { ur-3100r09v1Entry 6 }

		-- 1.3.6.1.4.1.10106.3.101291.1.1.7
		ur-3100r09v1VccVoltage OBJECT-TYPE
			SYNTAX VccVoltage
			MAX-ACCESS read-only
			STATUS current
			DESCRIPTION
				"Indicates the uC voltage"
		::= { ur-3100r09v1Entry 7 }

		-- 1.3.6.1.4.1.10106.3.101291.1.1.9
		ur-3100r09v1SerialNo OBJECT-TYPE
			SYNTAX SerialNo
			MAX-ACCESS read-only
			STATUS current
			DESCRIPTION
				"Serial number"
		::= { ur-3100r09v1Entry 9 }

		-- 1.3.6.1.4.1.10106.3.274401
		dvm3001c01v1 OBJECT IDENTIFIER ::= { albalaProducts 274401 }

		-- 1.3.6.1.4.1.10106.3.274401.1
		dvm3001c01v1Table  OBJECT-TYPE
			SYNTAX SEQUENCE OF Dvm3001c01v1Entry
			MAX-ACCESS not-accessible
			STATUS current
			DESCRIPTION
				"Module  DVM3001C01V1 Table"
			::= { dvm3001c01v1 1 }

		-- 1.3.6.1.4.1.10106.3.274401.1.1
		dvm3001c01v1Entry  OBJECT-TYPE
			SYNTAX Dvm3001c01v1Entry
			MAX-ACCESS not-accessible
			STATUS current
			DESCRIPTION
				"Module DVM3001C01V1 Entry"
			INDEX { dvm3001c01v1Index }
			::= { dvm3001c01v1Table 1 }

			Dvm3001c01v1Entry ::=
			SEQUENCE {
				dvm3001c01v1Index
				ModuleIndex,
				dvm3001c01v1VbiPassA
				Bit0Bnk1Pas,
				dvm3001c01v1VbiPassB
				Bit0Bnk1Pas,
				dvm3001c01v1ChromaA
				Bit0Off1On,
				dvm3001c01v1ChromaB
				Bit0Off1On,
				dvm3001c01v1LumaFilterA
				Bit0Not1Flt,
				dvm3001c01v1LumaFilterB
				Bit0Not1Flt,
				dvm3001c01v1CustomFilterA
				Bit0Cus1Std,
				dvm3001c01v1CustomFilterB
				Bit0Cus1Std,
				dvm3001c01v1Mode
				Bit0Sin1Dua,
				dvm3001c01v1NoSigA
				BitFail,
				dvm3001c01v1NoSigATrapEnable
				AlarmEnable,
				dvm3001c01v1NoSigB
				BitFail,
				dvm3001c01v1NoSigBTrapEnable
				AlarmEnable,
				dvm3001c01v1MaxEqA
				BitFail,
				dvm3001c01v1MaxEqB
				BitFail,
				dvm3001c01v1UnlockA
				BitFail,
				dvm3001c01v1UnlockATrapEnable
				AlarmEnable,
				dvm3001c01v1UnlockB
				BitFail,
				dvm3001c01v1UnlockBTrapEnable
				AlarmEnable,
				dvm3001c01v1EdhErrorA
				BitFail,
				dvm3001c01v1EdhErrorB
				BitFail,
				dvm3001c01v1EdhPresA
				Bit0No1Yes,
				dvm3001c01v1EdhPresB
				Bit0No1Yes,
				dvm3001c01v1FormatA
				Bit06251525,
				dvm3001c01v1FormatB
				Bit06251525,
				dvm3001c01v1MuteA
				Bit0No1Yes,
				dvm3001c01v1MuteB
				Bit0No1Yes,
				dvm3001c01v1CableLengthA
				Rate1,
				dvm3001c01v1CableLengthB
				Rate1,
				dvm3001c01v1SerialNo
				SerialNo
			 }

		-- 1.3.6.1.4.1.10106.3.101291.1.1.1
		dvm3001c01v1Index OBJECT-TYPE
			SYNTAX ModuleIndex
			MAX-ACCESS read-only
			STATUS current
			DESCRIPTION
				"Index of DVM3001C01V1 Table"
		::= { dvm3001c01v1Entry 1 }

		-- 1.3.6.1.4.1.10106.3.101291.1.1.3
		dvm3001c01v1VbiPassA OBJECT-TYPE
			SYNTAX Bit0Bnk1Pas
			MAX-ACCESS read-write
			STATUS current
			DESCRIPTION
				"Allows selecting if the VBI is blanked"
		::= { dvm3001c01v1Entry 3 }

		-- 1.3.6.1.4.1.10106.3.101291.1.1.5
		dvm3001c01v1VbiPassB OBJECT-TYPE
			SYNTAX Bit0Bnk1Pas
			MAX-ACCESS read-write
			STATUS current
			DESCRIPTION
				"Allows selecting if the VBI is blanked"
		::= { dvm3001c01v1Entry 5 }

		-- 1.3.6.1.4.1.10106.3.101291.1.1.7
		dvm3001c01v1ChromaA OBJECT-TYPE
			SYNTAX Bit0Off1On
			MAX-ACCESS read-write
			STATUS current
			DESCRIPTION
				"Allows disabling chroma"
		::= { dvm3001c01v1Entry 7 }

		-- 1.3.6.1.4.1.10106.3.101291.1.1.9
		dvm3001c01v1ChromaB OBJECT-TYPE
			SYNTAX Bit0Off1On
			MAX-ACCESS read-write
			STATUS current
			DESCRIPTION
				"Allows disabling chroma"
		::= { dvm3001c01v1Entry 9 }

		-- 1.3.6.1.4.1.10106.3.101291.1.1.11
		dvm3001c01v1LumaFilterA OBJECT-TYPE
			SYNTAX Bit0Not1Flt
			MAX-ACCESS read-write
			STATUS current
			DESCRIPTION
				"Allows selecting luminance filter"
		::= { dvm3001c01v1Entry 11 }

		-- 1.3.6.1.4.1.10106.3.101291.1.1.13
		dvm3001c01v1LumaFilterB OBJECT-TYPE
			SYNTAX Bit0Not1Flt
			MAX-ACCESS read-write
			STATUS current
			DESCRIPTION
				"Allows selecting luminance filter"
		::= { dvm3001c01v1Entry 13 }

		-- 1.3.6.1.4.1.10106.3.101291.1.1.15
		dvm3001c01v1CustomFilterA OBJECT-TYPE
			SYNTAX Bit0Cus1Std
			MAX-ACCESS read-write
			STATUS current
			DESCRIPTION
				"Allows selecting a custom luminance filter"
		::= { dvm3001c01v1Entry 15 }

		-- 1.3.6.1.4.1.10106.3.101291.1.1.17
		dvm3001c01v1CustomFilterB OBJECT-TYPE
			SYNTAX Bit0Cus1Std
			MAX-ACCESS read-write
			STATUS current
			DESCRIPTION
				"Allows selecting a custom luminance filter"
		::= { dvm3001c01v1Entry 17 }

		-- 1.3.6.1.4.1.10106.3.101291.1.1.19
		dvm3001c01v1Mode OBJECT-TYPE
			SYNTAX Bit0Sin1Dua
			MAX-ACCESS read-write
			STATUS current
			DESCRIPTION
				"Allows selecting module operating mode"
		::= { dvm3001c01v1Entry 19 }

		-- 1.3.6.1.4.1.10106.3.101291.1.1.21
		dvm3001c01v1NoSigA OBJECT-TYPE
			SYNTAX BitFail
			MAX-ACCESS read-only
			STATUS current
			DESCRIPTION
				"Input signal status"
		::= { dvm3001c01v1Entry 21 }

		-- 1.3.6.1.4.1.10106.3.101291.1.1.22
		dvm3001c01v1NoSigATrapEnable OBJECT-TYPE
			SYNTAX AlarmEnable
			MAX-ACCESS read-write
			STATUS current
			DESCRIPTION
				"Input signal status Trap Enable"
		::= { dvm3001c01v1Entry 22 }

		-- 1.3.6.1.4.1.10106.3.101291.1.1.23
		dvm3001c01v1NoSigB OBJECT-TYPE
			SYNTAX BitFail
			MAX-ACCESS read-only
			STATUS current
			DESCRIPTION
				"Input signal status"
		::= { dvm3001c01v1Entry 23 }

		-- 1.3.6.1.4.1.10106.3.101291.1.1.24
		dvm3001c01v1NoSigBTrapEnable OBJECT-TYPE
			SYNTAX AlarmEnable
			MAX-ACCESS read-write
			STATUS current
			DESCRIPTION
				"Input signal status Trap Enable"
		::= { dvm3001c01v1Entry 24 }

		-- 1.3.6.1.4.1.10106.3.101291.1.1.25
		dvm3001c01v1MaxEqA OBJECT-TYPE
			SYNTAX BitFail
			MAX-ACCESS read-only
			STATUS current
			DESCRIPTION
				"Indicates maximum equalization"
		::= { dvm3001c01v1Entry 25 }

		-- 1.3.6.1.4.1.10106.3.101291.1.1.27
		dvm3001c01v1MaxEqB OBJECT-TYPE
			SYNTAX BitFail
			MAX-ACCESS read-only
			STATUS current
			DESCRIPTION
				"Indicates maximum equalization"
		::= { dvm3001c01v1Entry 27 }

		-- 1.3.6.1.4.1.10106.3.101291.1.1.29
		dvm3001c01v1UnlockA OBJECT-TYPE
			SYNTAX BitFail
			MAX-ACCESS read-only
			STATUS current
			DESCRIPTION
				"Indicates signal unlock fail"
		::= { dvm3001c01v1Entry 29 }

		-- 1.3.6.1.4.1.10106.3.101291.1.1.30
		dvm3001c01v1UnlockATrapEnable OBJECT-TYPE
			SYNTAX AlarmEnable
			MAX-ACCESS read-write
			STATUS current
			DESCRIPTION
				"Indicates signal unlock fail Trap Enable"
		::= { dvm3001c01v1Entry 30 }

		-- 1.3.6.1.4.1.10106.3.101291.1.1.31
		dvm3001c01v1UnlockB OBJECT-TYPE
			SYNTAX BitFail
			MAX-ACCESS read-only
			STATUS current
			DESCRIPTION
				"Indicates signal unlock fail"
		::= { dvm3001c01v1Entry 31 }

		-- 1.3.6.1.4.1.10106.3.101291.1.1.32
		dvm3001c01v1UnlockBTrapEnable OBJECT-TYPE
			SYNTAX AlarmEnable
			MAX-ACCESS read-write
			STATUS current
			DESCRIPTION
				"Indicates signal unlock fail Trap Enable"
		::= { dvm3001c01v1Entry 32 }

		-- 1.3.6.1.4.1.10106.3.101291.1.1.33
		dvm3001c01v1EdhErrorA OBJECT-TYPE
			SYNTAX BitFail
			MAX-ACCESS read-only
			STATUS current
			DESCRIPTION
				"EDH status"
		::= { dvm3001c01v1Entry 33 }

		-- 1.3.6.1.4.1.10106.3.101291.1.1.35
		dvm3001c01v1EdhErrorB OBJECT-TYPE
			SYNTAX BitFail
			MAX-ACCESS read-only
			STATUS current
			DESCRIPTION
				"EDH status"
		::= { dvm3001c01v1Entry 35 }

		-- 1.3.6.1.4.1.10106.3.101291.1.1.37
		dvm3001c01v1EdhPresA OBJECT-TYPE
			SYNTAX Bit0No1Yes
			MAX-ACCESS read-only
			STATUS current
			DESCRIPTION
				"EDH packet presence"
		::= { dvm3001c01v1Entry 37 }

		-- 1.3.6.1.4.1.10106.3.101291.1.1.39
		dvm3001c01v1EdhPresB OBJECT-TYPE
			SYNTAX Bit0No1Yes
			MAX-ACCESS read-only
			STATUS current
			DESCRIPTION
				"EDH packet presence"
		::= { dvm3001c01v1Entry 39 }

		-- 1.3.6.1.4.1.10106.3.101291.1.1.41
		dvm3001c01v1FormatA OBJECT-TYPE
			SYNTAX Bit06251525
			MAX-ACCESS read-only
			STATUS current
			DESCRIPTION
				"Format"
		::= { dvm3001c01v1Entry 41 }

		-- 1.3.6.1.4.1.10106.3.101291.1.1.43
		dvm3001c01v1FormatB OBJECT-TYPE
			SYNTAX Bit06251525
			MAX-ACCESS read-only
			STATUS current
			DESCRIPTION
				"Format"
		::= { dvm3001c01v1Entry 43 }

		-- 1.3.6.1.4.1.10106.3.101291.1.1.45
		dvm3001c01v1MuteA OBJECT-TYPE
			SYNTAX Bit0No1Yes
			MAX-ACCESS read-only
			STATUS current
			DESCRIPTION
				"Output muted"
		::= { dvm3001c01v1Entry 45 }

		-- 1.3.6.1.4.1.10106.3.101291.1.1.47
		dvm3001c01v1MuteB OBJECT-TYPE
			SYNTAX Bit0No1Yes
			MAX-ACCESS read-only
			STATUS current
			DESCRIPTION
				"Output muted"
		::= { dvm3001c01v1Entry 47 }

		-- 1.3.6.1.4.1.10106.3.101291.1.1.49
		dvm3001c01v1CableLengthA OBJECT-TYPE
			SYNTAX Rate1
			MAX-ACCESS read-only
			STATUS current
			DESCRIPTION
				"Equalization level refered to maximun"
		::= { dvm3001c01v1Entry 49 }

		-- 1.3.6.1.4.1.10106.3.101291.1.1.51
		dvm3001c01v1CableLengthB OBJECT-TYPE
			SYNTAX Rate1
			MAX-ACCESS read-only
			STATUS current
			DESCRIPTION
				"Equalization level refered to maximun"
		::= { dvm3001c01v1Entry 51 }

		-- 1.3.6.1.4.1.10106.3.101291.1.1.53
		dvm3001c01v1SerialNo OBJECT-TYPE
			SYNTAX SerialNo
			MAX-ACCESS read-only
			STATUS current
			DESCRIPTION
				"Serial number"
		::= { dvm3001c01v1Entry 53 }

		-- 1.3.6.1.4.1.10106.3.275101
		dsw3001c01v1 OBJECT IDENTIFIER ::= { albalaProducts 275101 }

		-- 1.3.6.1.4.1.10106.3.275101.1
		dsw3001c01v1Table  OBJECT-TYPE
			SYNTAX SEQUENCE OF Dsw3001c01v1Entry
			MAX-ACCESS not-accessible
			STATUS current
			DESCRIPTION
				"Module  DSW3001C01V1 Table"
			::= { dsw3001c01v1 1 }

		-- 1.3.6.1.4.1.10106.3.275101.1.1
		dsw3001c01v1Entry  OBJECT-TYPE
			SYNTAX Dsw3001c01v1Entry
			MAX-ACCESS not-accessible
			STATUS current
			DESCRIPTION
				"Module DSW3001C01V1 Entry"
			INDEX { dsw3001c01v1Index }
			::= { dsw3001c01v1Table 1 }

			Dsw3001c01v1Entry ::=
			SEQUENCE {
				dsw3001c01v1Index
				ModuleIndex,
				dsw3001c01v1Mode
				ChgOverMode2,
				dsw3001c01v1ModeTrapEnable
				AlarmEnable,
				dsw3001c01v1Output
				Bit0Ts1Mr,
				dsw3001c01v1OutSignal
				Bit0Nos1Tes,
				dsw3001c01v1TestSignal
				Bit0Cb1Bb,
				dsw3001c01v1Format
				Bit06251525,
				dsw3001c01v1Input
				ChgOverInput2,
				dsw3001c01v1InputTrapEnable
				AlarmEnable,
				dsw3001c01v1InputChange
				Bit0No1Yes,
				dsw3001c01v1ExtInpMMask
				BitMask,
				dsw3001c01v1NoSigMMask
				BitMask,
				dsw3001c01v1BadFmtMMask
				BitMask,
				dsw3001c01v1EdhErrMMask
				BitMask,
				dsw3001c01v1EdhPckMMask
				BitMask,
				dsw3001c01v1PatternMMask
				BitMask,
				dsw3001c01v1BlackMMask
				BitMask,
				dsw3001c01v1FreezeMMask
				BitMask,
				dsw3001c01v1ExtInpRMask
				BitMask,
				dsw3001c01v1NoSigRMask
				BitMask,
				dsw3001c01v1BadFmtRMask
				BitMask,
				dsw3001c01v1EdhErrRMask
				BitMask,
				dsw3001c01v1EdhPckRMask
				BitMask,
				dsw3001c01v1PatternRMask
				BitMask,
				dsw3001c01v1BlackRMask
				BitMask,
				dsw3001c01v1FreezeRMask
				BitMask,
				dsw3001c01v1PresMMask
				BitMask,
				dsw3001c01v1SilMMask
				BitMask,
				dsw3001c01v1OvlMMask
				BitMask,
				dsw3001c01v1AntiphMMask
				BitMask,
				dsw3001c01v1PresRMask
				BitMask,
				dsw3001c01v1SilRMask
				BitMask,
				dsw3001c01v1OvlRMask
				BitMask,
				dsw3001c01v1AntiphRMask
				BitMask,
				dsw3001c01v1AudCh9MMask
				BitMask,
				dsw3001c01v1AudCh10MMask
				BitMask,
				dsw3001c01v1AudCh11MMask
				BitMask,
				dsw3001c01v1AudCh12MMask
				BitMask,
				dsw3001c01v1AudCh13MMask
				BitMask,
				dsw3001c01v1AudCh14MMask
				BitMask,
				dsw3001c01v1AudCh15MMask
				BitMask,
				dsw3001c01v1AudCh16MMask
				BitMask,
				dsw3001c01v1AudCh1MMask
				BitMask,
				dsw3001c01v1AudCh2MMask
				BitMask,
				dsw3001c01v1AudCh3MMask
				BitMask,
				dsw3001c01v1AudCh4MMask
				BitMask,
				dsw3001c01v1AudCh5MMask
				BitMask,
				dsw3001c01v1AudCh6MMask
				BitMask,
				dsw3001c01v1AudCh7MMask
				BitMask,
				dsw3001c01v1AudCh8MMask
				BitMask,
				dsw3001c01v1AudCh9RMask
				BitMask,
				dsw3001c01v1AudCh10RMask
				BitMask,
				dsw3001c01v1AudCh11RMask
				BitMask,
				dsw3001c01v1AudCh12RMask
				BitMask,
				dsw3001c01v1AudCh13RMask
				BitMask,
				dsw3001c01v1AudCh14RMask
				BitMask,
				dsw3001c01v1AudCh15RMask
				BitMask,
				dsw3001c01v1AudCh16RMask
				BitMask,
				dsw3001c01v1AudCh1RMask
				BitMask,
				dsw3001c01v1AudCh2RMask
				BitMask,
				dsw3001c01v1AudCh3RMask
				BitMask,
				dsw3001c01v1AudCh4RMask
				BitMask,
				dsw3001c01v1AudCh5RMask
				BitMask,
				dsw3001c01v1AudCh6RMask
				BitMask,
				dsw3001c01v1AudCh7RMask
				BitMask,
				dsw3001c01v1AudCh8RMask
				BitMask,
				dsw3001c01v1BlckFrzTimeout
				DelayFram2,
				dsw3001c01v1OverloadLevel
				LevelDbfs1,
				dsw3001c01v1SilenceLevel
				LevelDbfs1,
				dsw3001c01v1SilenceTime
				TimeS2,
				dsw3001c01v1VideoFailM
				BitFail,
				dsw3001c01v1VideoFailMTrapEnable
				AlarmEnable,
				dsw3001c01v1VideoFailR
				BitFail,
				dsw3001c01v1VideoFailRTrapEnable
				AlarmEnable,
				dsw3001c01v1AudioFailM
				BitFail,
				dsw3001c01v1AudioFailMTrapEnable
				AlarmEnable,
				dsw3001c01v1AudioFailR
				BitFail,
				dsw3001c01v1AudioFailRTrapEnable
				AlarmEnable,
				dsw3001c01v1ExtInpM
				BitFail,
				dsw3001c01v1NoSigM
				BitFail,
				dsw3001c01v1BadFmtM
				BitFail,
				dsw3001c01v1EdhErrM
				BitFail,
				dsw3001c01v1EdhPckM
				BitFail,
				dsw3001c01v1PatternM
				BitFail,
				dsw3001c01v1BlackM
				BitFail,
				dsw3001c01v1FreezeM
				BitFail,
				dsw3001c01v1PresM
				BitFail,
				dsw3001c01v1SilM
				BitFail,
				dsw3001c01v1OvlM
				BitFail,
				dsw3001c01v1AntiphM
				BitFail,
				dsw3001c01v1ExtInpR
				BitFail,
				dsw3001c01v1NoSigR
				BitFail,
				dsw3001c01v1BadFmtR
				BitFail,
				dsw3001c01v1EdhErrR
				BitFail,
				dsw3001c01v1EdhPckR
				BitFail,
				dsw3001c01v1PatternR
				BitFail,
				dsw3001c01v1BlackR
				BitFail,
				dsw3001c01v1FreezeR
				BitFail,
				dsw3001c01v1PresR
				BitFail,
				dsw3001c01v1SilR
				BitFail,
				dsw3001c01v1OvlR
				BitFail,
				dsw3001c01v1AntiphR
				BitFail
			 }

		-- 1.3.6.1.4.1.10106.3.101291.1.1.1
		dsw3001c01v1Index OBJECT-TYPE
			SYNTAX ModuleIndex
			MAX-ACCESS read-only
			STATUS current
			DESCRIPTION
				"Index of DSW3001C01V1 Table"
		::= { dsw3001c01v1Entry 1 }

		-- 1.3.6.1.4.1.10106.3.101291.1.1.3
		dsw3001c01v1Mode OBJECT-TYPE
			SYNTAX ChgOverMode2
			MAX-ACCESS read-write
			STATUS current
			DESCRIPTION
				"Allows selecting the switching mode"
		::= { dsw3001c01v1Entry 3 }

		-- 1.3.6.1.4.1.10106.3.101291.1.1.4
		dsw3001c01v1ModeTrapEnable OBJECT-TYPE
			SYNTAX AlarmEnable
			MAX-ACCESS read-write
			STATUS current
			DESCRIPTION
				"Allows selecting the switching mode Trap Enable"
		::= { dsw3001c01v1Entry 4 }

		-- 1.3.6.1.4.1.10106.3.101291.1.1.5
		dsw3001c01v1Output OBJECT-TYPE
			SYNTAX Bit0Ts1Mr
			MAX-ACCESS read-write
			STATUS current
			DESCRIPTION
				"Selects the outputs signal in the case of fail on both inputs"
		::= { dsw3001c01v1Entry 5 }

		-- 1.3.6.1.4.1.10106.3.101291.1.1.7
		dsw3001c01v1OutSignal OBJECT-TYPE
			SYNTAX Bit0Nos1Tes
			MAX-ACCESS read-write
			STATUS current
			DESCRIPTION
				"Selects the output behaviour in case of severe fail in both inputs"
		::= { dsw3001c01v1Entry 7 }

		-- 1.3.6.1.4.1.10106.3.101291.1.1.9
		dsw3001c01v1TestSignal OBJECT-TYPE
			SYNTAX Bit0Cb1Bb
			MAX-ACCESS read-write
			STATUS current
			DESCRIPTION
				"Allows selecting the generated signal"
		::= { dsw3001c01v1Entry 9 }

		-- 1.3.6.1.4.1.10106.3.101291.1.1.11
		dsw3001c01v1Format OBJECT-TYPE
			SYNTAX Bit06251525
			MAX-ACCESS read-write
			STATUS current
			DESCRIPTION
				"Format"
		::= { dsw3001c01v1Entry 11 }

		-- 1.3.6.1.4.1.10106.3.101291.1.1.13
		dsw3001c01v1Input OBJECT-TYPE
			SYNTAX ChgOverInput2
			MAX-ACCESS read-write
			STATUS current
			DESCRIPTION
				"Selected input"
		::= { dsw3001c01v1Entry 13 }

		-- 1.3.6.1.4.1.10106.3.101291.1.1.14
		dsw3001c01v1InputTrapEnable OBJECT-TYPE
			SYNTAX AlarmEnable
			MAX-ACCESS read-write
			STATUS current
			DESCRIPTION
				"Selected input Trap Enable"
		::= { dsw3001c01v1Entry 14 }

		-- 1.3.6.1.4.1.10106.3.101291.1.1.15
		dsw3001c01v1InputChange OBJECT-TYPE
			SYNTAX Bit0No1Yes
			MAX-ACCESS read-write
			STATUS current
			DESCRIPTION
				"Signals a change in selected input"
		::= { dsw3001c01v1Entry 15 }

		-- 1.3.6.1.4.1.10106.3.101291.1.1.17
		dsw3001c01v1ExtInpMMask OBJECT-TYPE
			SYNTAX BitMask
			MAX-ACCESS read-write
			STATUS current
			DESCRIPTION
				"Allows masking the external fail (GPI)"
		::= { dsw3001c01v1Entry 17 }

		-- 1.3.6.1.4.1.10106.3.101291.1.1.19
		dsw3001c01v1NoSigMMask OBJECT-TYPE
			SYNTAX BitMask
			MAX-ACCESS read-write
			STATUS current
			DESCRIPTION
				"Allows masking the no SDI signal fail"
		::= { dsw3001c01v1Entry 19 }

		-- 1.3.6.1.4.1.10106.3.101291.1.1.21
		dsw3001c01v1BadFmtMMask OBJECT-TYPE
			SYNTAX BitMask
			MAX-ACCESS read-write
			STATUS current
			DESCRIPTION
				"Allows masking the bad SDI format fail"
		::= { dsw3001c01v1Entry 21 }

		-- 1.3.6.1.4.1.10106.3.101291.1.1.23
		dsw3001c01v1EdhErrMMask OBJECT-TYPE
			SYNTAX BitMask
			MAX-ACCESS read-write
			STATUS current
			DESCRIPTION
				"Allows masking the EDH error fail"
		::= { dsw3001c01v1Entry 23 }

		-- 1.3.6.1.4.1.10106.3.101291.1.1.25
		dsw3001c01v1EdhPckMMask OBJECT-TYPE
			SYNTAX BitMask
			MAX-ACCESS read-write
			STATUS current
			DESCRIPTION
				"Allows masking the no EDH packets presence fail"
		::= { dsw3001c01v1Entry 25 }

		-- 1.3.6.1.4.1.10106.3.101291.1.1.27
		dsw3001c01v1PatternMMask OBJECT-TYPE
			SYNTAX BitMask
			MAX-ACCESS read-write
			STATUS current
			DESCRIPTION
				"Allows masking the fixed pattern fail"
		::= { dsw3001c01v1Entry 27 }

		-- 1.3.6.1.4.1.10106.3.101291.1.1.29
		dsw3001c01v1BlackMMask OBJECT-TYPE
			SYNTAX BitMask
			MAX-ACCESS read-write
			STATUS current
			DESCRIPTION
				"Allows masking the black pattern fail"
		::= { dsw3001c01v1Entry 29 }

		-- 1.3.6.1.4.1.10106.3.101291.1.1.31
		dsw3001c01v1FreezeMMask OBJECT-TYPE
			SYNTAX BitMask
			MAX-ACCESS read-write
			STATUS current
			DESCRIPTION
				"Allows masking the freeze image fail"
		::= { dsw3001c01v1Entry 31 }

		-- 1.3.6.1.4.1.10106.3.101291.1.1.33
		dsw3001c01v1ExtInpRMask OBJECT-TYPE
			SYNTAX BitMask
			MAX-ACCESS read-write
			STATUS current
			DESCRIPTION
				"Allows masking the external fail (GPI)"
		::= { dsw3001c01v1Entry 33 }

		-- 1.3.6.1.4.1.10106.3.101291.1.1.35
		dsw3001c01v1NoSigRMask OBJECT-TYPE
			SYNTAX BitMask
			MAX-ACCESS read-write
			STATUS current
			DESCRIPTION
				"Allows masking the no SDI signal fail"
		::= { dsw3001c01v1Entry 35 }

		-- 1.3.6.1.4.1.10106.3.101291.1.1.37
		dsw3001c01v1BadFmtRMask OBJECT-TYPE
			SYNTAX BitMask
			MAX-ACCESS read-write
			STATUS current
			DESCRIPTION
				"Allows masking the bad SDI format fail"
		::= { dsw3001c01v1Entry 37 }

		-- 1.3.6.1.4.1.10106.3.101291.1.1.39
		dsw3001c01v1EdhErrRMask OBJECT-TYPE
			SYNTAX BitMask
			MAX-ACCESS read-write
			STATUS current
			DESCRIPTION
				"Allows masking the EDH error fail"
		::= { dsw3001c01v1Entry 39 }

		-- 1.3.6.1.4.1.10106.3.101291.1.1.41
		dsw3001c01v1EdhPckRMask OBJECT-TYPE
			SYNTAX BitMask
			MAX-ACCESS read-write
			STATUS current
			DESCRIPTION
				"Allows masking the no EDH packets presence fail"
		::= { dsw3001c01v1Entry 41 }

		-- 1.3.6.1.4.1.10106.3.101291.1.1.43
		dsw3001c01v1PatternRMask OBJECT-TYPE
			SYNTAX BitMask
			MAX-ACCESS read-write
			STATUS current
			DESCRIPTION
				"Allows masking the fixed pattern fail"
		::= { dsw3001c01v1Entry 43 }

		-- 1.3.6.1.4.1.10106.3.101291.1.1.45
		dsw3001c01v1BlackRMask OBJECT-TYPE
			SYNTAX BitMask
			MAX-ACCESS read-write
			STATUS current
			DESCRIPTION
				"Allows masking the black pattern fail"
		::= { dsw3001c01v1Entry 45 }

		-- 1.3.6.1.4.1.10106.3.101291.1.1.47
		dsw3001c01v1FreezeRMask OBJECT-TYPE
			SYNTAX BitMask
			MAX-ACCESS read-write
			STATUS current
			DESCRIPTION
				"Allows masking the freeze image fail"
		::= { dsw3001c01v1Entry 47 }

		-- 1.3.6.1.4.1.10106.3.101291.1.1.49
		dsw3001c01v1PresMMask OBJECT-TYPE
			SYNTAX BitMask
			MAX-ACCESS read-write
			STATUS current
			DESCRIPTION
				"Allows masking the no audio presence fail"
		::= { dsw3001c01v1Entry 49 }

		-- 1.3.6.1.4.1.10106.3.101291.1.1.51
		dsw3001c01v1SilMMask OBJECT-TYPE
			SYNTAX BitMask
			MAX-ACCESS read-write
			STATUS current
			DESCRIPTION
				"Allows masking the audio silence fail"
		::= { dsw3001c01v1Entry 51 }

		-- 1.3.6.1.4.1.10106.3.101291.1.1.53
		dsw3001c01v1OvlMMask OBJECT-TYPE
			SYNTAX BitMask
			MAX-ACCESS read-write
			STATUS current
			DESCRIPTION
				"Allows masking the audio overload fail"
		::= { dsw3001c01v1Entry 53 }

		-- 1.3.6.1.4.1.10106.3.101291.1.1.55
		dsw3001c01v1AntiphMMask OBJECT-TYPE
			SYNTAX BitMask
			MAX-ACCESS read-write
			STATUS current
			DESCRIPTION
				"Allows masking the audio antiphase fail"
		::= { dsw3001c01v1Entry 55 }

		-- 1.3.6.1.4.1.10106.3.101291.1.1.57
		dsw3001c01v1PresRMask OBJECT-TYPE
			SYNTAX BitMask
			MAX-ACCESS read-write
			STATUS current
			DESCRIPTION
				"Allows masking the no audio presence fail"
		::= { dsw3001c01v1Entry 57 }

		-- 1.3.6.1.4.1.10106.3.101291.1.1.59
		dsw3001c01v1SilRMask OBJECT-TYPE
			SYNTAX BitMask
			MAX-ACCESS read-write
			STATUS current
			DESCRIPTION
				"Allows masking the audio silence fail"
		::= { dsw3001c01v1Entry 59 }

		-- 1.3.6.1.4.1.10106.3.101291.1.1.61
		dsw3001c01v1OvlRMask OBJECT-TYPE
			SYNTAX BitMask
			MAX-ACCESS read-write
			STATUS current
			DESCRIPTION
				"Allows masking the audio overload fail"
		::= { dsw3001c01v1Entry 61 }

		-- 1.3.6.1.4.1.10106.3.101291.1.1.63
		dsw3001c01v1AntiphRMask OBJECT-TYPE
			SYNTAX BitMask
			MAX-ACCESS read-write
			STATUS current
			DESCRIPTION
				"Allows masking the audio antiphase fail"
		::= { dsw3001c01v1Entry 63 }

		-- 1.3.6.1.4.1.10106.3.101291.1.1.65
		dsw3001c01v1AudCh9MMask OBJECT-TYPE
			SYNTAX BitMask
			MAX-ACCESS read-write
			STATUS current
			DESCRIPTION
				"Allows masking the audio channel 9"
		::= { dsw3001c01v1Entry 65 }

		-- 1.3.6.1.4.1.10106.3.101291.1.1.67
		dsw3001c01v1AudCh10MMask OBJECT-TYPE
			SYNTAX BitMask
			MAX-ACCESS read-write
			STATUS current
			DESCRIPTION
				"Allows masking the audio channel 10"
		::= { dsw3001c01v1Entry 67 }

		-- 1.3.6.1.4.1.10106.3.101291.1.1.69
		dsw3001c01v1AudCh11MMask OBJECT-TYPE
			SYNTAX BitMask
			MAX-ACCESS read-write
			STATUS current
			DESCRIPTION
				"Allows masking the audio channel 11"
		::= { dsw3001c01v1Entry 69 }

		-- 1.3.6.1.4.1.10106.3.101291.1.1.71
		dsw3001c01v1AudCh12MMask OBJECT-TYPE
			SYNTAX BitMask
			MAX-ACCESS read-write
			STATUS current
			DESCRIPTION
				"Allows masking the audio channel 12"
		::= { dsw3001c01v1Entry 71 }

		-- 1.3.6.1.4.1.10106.3.101291.1.1.73
		dsw3001c01v1AudCh13MMask OBJECT-TYPE
			SYNTAX BitMask
			MAX-ACCESS read-write
			STATUS current
			DESCRIPTION
				"Allows masking the audio channel 13"
		::= { dsw3001c01v1Entry 73 }

		-- 1.3.6.1.4.1.10106.3.101291.1.1.75
		dsw3001c01v1AudCh14MMask OBJECT-TYPE
			SYNTAX BitMask
			MAX-ACCESS read-write
			STATUS current
			DESCRIPTION
				"Allows masking the audio channel 14"
		::= { dsw3001c01v1Entry 75 }

		-- 1.3.6.1.4.1.10106.3.101291.1.1.77
		dsw3001c01v1AudCh15MMask OBJECT-TYPE
			SYNTAX BitMask
			MAX-ACCESS read-write
			STATUS current
			DESCRIPTION
				"Allows masking the audio channel 15"
		::= { dsw3001c01v1Entry 77 }

		-- 1.3.6.1.4.1.10106.3.101291.1.1.79
		dsw3001c01v1AudCh16MMask OBJECT-TYPE
			SYNTAX BitMask
			MAX-ACCESS read-write
			STATUS current
			DESCRIPTION
				"Allows masking the audio channel 16"
		::= { dsw3001c01v1Entry 79 }

		-- 1.3.6.1.4.1.10106.3.101291.1.1.81
		dsw3001c01v1AudCh1MMask OBJECT-TYPE
			SYNTAX BitMask
			MAX-ACCESS read-write
			STATUS current
			DESCRIPTION
				"Allows masking the audio channel 1"
		::= { dsw3001c01v1Entry 81 }

		-- 1.3.6.1.4.1.10106.3.101291.1.1.83
		dsw3001c01v1AudCh2MMask OBJECT-TYPE
			SYNTAX BitMask
			MAX-ACCESS read-write
			STATUS current
			DESCRIPTION
				"Allows masking the audio channel 2"
		::= { dsw3001c01v1Entry 83 }

		-- 1.3.6.1.4.1.10106.3.101291.1.1.85
		dsw3001c01v1AudCh3MMask OBJECT-TYPE
			SYNTAX BitMask
			MAX-ACCESS read-write
			STATUS current
			DESCRIPTION
				"Allows masking the audio channel 3"
		::= { dsw3001c01v1Entry 85 }

		-- 1.3.6.1.4.1.10106.3.101291.1.1.87
		dsw3001c01v1AudCh4MMask OBJECT-TYPE
			SYNTAX BitMask
			MAX-ACCESS read-write
			STATUS current
			DESCRIPTION
				"Allows masking the audio channel 4"
		::= { dsw3001c01v1Entry 87 }

		-- 1.3.6.1.4.1.10106.3.101291.1.1.89
		dsw3001c01v1AudCh5MMask OBJECT-TYPE
			SYNTAX BitMask
			MAX-ACCESS read-write
			STATUS current
			DESCRIPTION
				"Allows masking the audio channel 5"
		::= { dsw3001c01v1Entry 89 }

		-- 1.3.6.1.4.1.10106.3.101291.1.1.91
		dsw3001c01v1AudCh6MMask OBJECT-TYPE
			SYNTAX BitMask
			MAX-ACCESS read-write
			STATUS current
			DESCRIPTION
				"Allows masking the audio channel 6"
		::= { dsw3001c01v1Entry 91 }

		-- 1.3.6.1.4.1.10106.3.101291.1.1.93
		dsw3001c01v1AudCh7MMask OBJECT-TYPE
			SYNTAX BitMask
			MAX-ACCESS read-write
			STATUS current
			DESCRIPTION
				"Allows masking the audio channel 7"
		::= { dsw3001c01v1Entry 93 }

		-- 1.3.6.1.4.1.10106.3.101291.1.1.95
		dsw3001c01v1AudCh8MMask OBJECT-TYPE
			SYNTAX BitMask
			MAX-ACCESS read-write
			STATUS current
			DESCRIPTION
				"Allows masking the audio channel 8"
		::= { dsw3001c01v1Entry 95 }

		-- 1.3.6.1.4.1.10106.3.101291.1.1.97
		dsw3001c01v1AudCh9RMask OBJECT-TYPE
			SYNTAX BitMask
			MAX-ACCESS read-write
			STATUS current
			DESCRIPTION
				"Allows masking the audio channel 9"
		::= { dsw3001c01v1Entry 97 }

		-- 1.3.6.1.4.1.10106.3.101291.1.1.99
		dsw3001c01v1AudCh10RMask OBJECT-TYPE
			SYNTAX BitMask
			MAX-ACCESS read-write
			STATUS current
			DESCRIPTION
				"Allows masking the audio channel 10"
		::= { dsw3001c01v1Entry 99 }

		-- 1.3.6.1.4.1.10106.3.101291.1.1.101
		dsw3001c01v1AudCh11RMask OBJECT-TYPE
			SYNTAX BitMask
			MAX-ACCESS read-write
			STATUS current
			DESCRIPTION
				"Allows masking the audio channel 11"
		::= { dsw3001c01v1Entry 101 }

		-- 1.3.6.1.4.1.10106.3.101291.1.1.103
		dsw3001c01v1AudCh12RMask OBJECT-TYPE
			SYNTAX BitMask
			MAX-ACCESS read-write
			STATUS current
			DESCRIPTION
				"Allows masking the audio channel 12"
		::= { dsw3001c01v1Entry 103 }

		-- 1.3.6.1.4.1.10106.3.101291.1.1.105
		dsw3001c01v1AudCh13RMask OBJECT-TYPE
			SYNTAX BitMask
			MAX-ACCESS read-write
			STATUS current
			DESCRIPTION
				"Allows masking the audio channel 13"
		::= { dsw3001c01v1Entry 105 }

		-- 1.3.6.1.4.1.10106.3.101291.1.1.107
		dsw3001c01v1AudCh14RMask OBJECT-TYPE
			SYNTAX BitMask
			MAX-ACCESS read-write
			STATUS current
			DESCRIPTION
				"Allows masking the audio channel 14"
		::= { dsw3001c01v1Entry 107 }

		-- 1.3.6.1.4.1.10106.3.101291.1.1.109
		dsw3001c01v1AudCh15RMask OBJECT-TYPE
			SYNTAX BitMask
			MAX-ACCESS read-write
			STATUS current
			DESCRIPTION
				"Allows masking the audio channel 15"
		::= { dsw3001c01v1Entry 109 }

		-- 1.3.6.1.4.1.10106.3.101291.1.1.111
		dsw3001c01v1AudCh16RMask OBJECT-TYPE
			SYNTAX BitMask
			MAX-ACCESS read-write
			STATUS current
			DESCRIPTION
				"Allows masking the audio channel 16"
		::= { dsw3001c01v1Entry 111 }

		-- 1.3.6.1.4.1.10106.3.101291.1.1.113
		dsw3001c01v1AudCh1RMask OBJECT-TYPE
			SYNTAX BitMask
			MAX-ACCESS read-write
			STATUS current
			DESCRIPTION
				"Allows masking the audio channel 1"
		::= { dsw3001c01v1Entry 113 }

		-- 1.3.6.1.4.1.10106.3.101291.1.1.115
		dsw3001c01v1AudCh2RMask OBJECT-TYPE
			SYNTAX BitMask
			MAX-ACCESS read-write
			STATUS current
			DESCRIPTION
				"Allows masking the audio channel 2"
		::= { dsw3001c01v1Entry 115 }

		-- 1.3.6.1.4.1.10106.3.101291.1.1.117
		dsw3001c01v1AudCh3RMask OBJECT-TYPE
			SYNTAX BitMask
			MAX-ACCESS read-write
			STATUS current
			DESCRIPTION
				"Allows masking the audio channel 3"
		::= { dsw3001c01v1Entry 117 }

		-- 1.3.6.1.4.1.10106.3.101291.1.1.119
		dsw3001c01v1AudCh4RMask OBJECT-TYPE
			SYNTAX BitMask
			MAX-ACCESS read-write
			STATUS current
			DESCRIPTION
				"Allows masking the audio channel 4"
		::= { dsw3001c01v1Entry 119 }

		-- 1.3.6.1.4.1.10106.3.101291.1.1.121
		dsw3001c01v1AudCh5RMask OBJECT-TYPE
			SYNTAX BitMask
			MAX-ACCESS read-write
			STATUS current
			DESCRIPTION
				"Allows masking the audio channel 5"
		::= { dsw3001c01v1Entry 121 }

		-- 1.3.6.1.4.1.10106.3.101291.1.1.123
		dsw3001c01v1AudCh6RMask OBJECT-TYPE
			SYNTAX BitMask
			MAX-ACCESS read-write
			STATUS current
			DESCRIPTION
				"Allows masking the audio channel 6"
		::= { dsw3001c01v1Entry 123 }

		-- 1.3.6.1.4.1.10106.3.101291.1.1.125
		dsw3001c01v1AudCh7RMask OBJECT-TYPE
			SYNTAX BitMask
			MAX-ACCESS read-write
			STATUS current
			DESCRIPTION
				"Allows masking the audio channel 7"
		::= { dsw3001c01v1Entry 125 }

		-- 1.3.6.1.4.1.10106.3.101291.1.1.127
		dsw3001c01v1AudCh8RMask OBJECT-TYPE
			SYNTAX BitMask
			MAX-ACCESS read-write
			STATUS current
			DESCRIPTION
				"Allows masking the audio channel 8"
		::= { dsw3001c01v1Entry 127 }

		-- 1.3.6.1.4.1.10106.3.101291.1.1.129
		dsw3001c01v1BlckFrzTimeout OBJECT-TYPE
			SYNTAX DelayFram2
			MAX-ACCESS read-write
			STATUS current
			DESCRIPTION
				"Allows selecting the black/freeze detection timeout"
		::= { dsw3001c01v1Entry 129 }

		-- 1.3.6.1.4.1.10106.3.101291.1.1.131
		dsw3001c01v1OverloadLevel OBJECT-TYPE
			SYNTAX LevelDbfs1
			MAX-ACCESS read-write
			STATUS current
			DESCRIPTION
				"Allows adjusting the threshold level for the overload detector"
		::= { dsw3001c01v1Entry 131 }

		-- 1.3.6.1.4.1.10106.3.101291.1.1.133
		dsw3001c01v1SilenceLevel OBJECT-TYPE
			SYNTAX LevelDbfs1
			MAX-ACCESS read-write
			STATUS current
			DESCRIPTION
				"Allows adjusting the threshold level for the silence detector"
		::= { dsw3001c01v1Entry 133 }

		-- 1.3.6.1.4.1.10106.3.101291.1.1.135
		dsw3001c01v1SilenceTime OBJECT-TYPE
			SYNTAX TimeS2
			MAX-ACCESS read-write
			STATUS current
			DESCRIPTION
				"Allows adjusting the time for the silence detector"
		::= { dsw3001c01v1Entry 135 }

		-- 1.3.6.1.4.1.10106.3.101291.1.1.137
		dsw3001c01v1VideoFailM OBJECT-TYPE
			SYNTAX BitFail
			MAX-ACCESS read-only
			STATUS current
			DESCRIPTION
				"Indicates that any video fail is active in main input"
		::= { dsw3001c01v1Entry 137 }

		-- 1.3.6.1.4.1.10106.3.101291.1.1.138
		dsw3001c01v1VideoFailMTrapEnable OBJECT-TYPE
			SYNTAX AlarmEnable
			MAX-ACCESS read-write
			STATUS current
			DESCRIPTION
				"Indicates that any video fail is active in main input Trap Enable"
		::= { dsw3001c01v1Entry 138 }

		-- 1.3.6.1.4.1.10106.3.101291.1.1.139
		dsw3001c01v1VideoFailR OBJECT-TYPE
			SYNTAX BitFail
			MAX-ACCESS read-only
			STATUS current
			DESCRIPTION
				"Indicates that any video fail is active in reserve input"
		::= { dsw3001c01v1Entry 139 }

		-- 1.3.6.1.4.1.10106.3.101291.1.1.140
		dsw3001c01v1VideoFailRTrapEnable OBJECT-TYPE
			SYNTAX AlarmEnable
			MAX-ACCESS read-write
			STATUS current
			DESCRIPTION
				"Indicates that any video fail is active in reserve input Trap Enable"
		::= { dsw3001c01v1Entry 140 }

		-- 1.3.6.1.4.1.10106.3.101291.1.1.141
		dsw3001c01v1AudioFailM OBJECT-TYPE
			SYNTAX BitFail
			MAX-ACCESS read-only
			STATUS current
			DESCRIPTION
				"Indicates that any audio fail is active in main input"
		::= { dsw3001c01v1Entry 141 }

		-- 1.3.6.1.4.1.10106.3.101291.1.1.142
		dsw3001c01v1AudioFailMTrapEnable OBJECT-TYPE
			SYNTAX AlarmEnable
			MAX-ACCESS read-write
			STATUS current
			DESCRIPTION
				"Indicates that any audio fail is active in main input Trap Enable"
		::= { dsw3001c01v1Entry 142 }

		-- 1.3.6.1.4.1.10106.3.101291.1.1.143
		dsw3001c01v1AudioFailR OBJECT-TYPE
			SYNTAX BitFail
			MAX-ACCESS read-only
			STATUS current
			DESCRIPTION
				"Indicates that any audio fail is active in reserve input"
		::= { dsw3001c01v1Entry 143 }

		-- 1.3.6.1.4.1.10106.3.101291.1.1.144
		dsw3001c01v1AudioFailRTrapEnable OBJECT-TYPE
			SYNTAX AlarmEnable
			MAX-ACCESS read-write
			STATUS current
			DESCRIPTION
				"Indicates that any audio fail is active in reserve input Trap Enable"
		::= { dsw3001c01v1Entry 144 }

		-- 1.3.6.1.4.1.10106.3.101291.1.1.145
		dsw3001c01v1ExtInpM OBJECT-TYPE
			SYNTAX BitFail
			MAX-ACCESS read-only
			STATUS current
			DESCRIPTION
				"Indicates external fail (GPI)"
		::= { dsw3001c01v1Entry 145 }

		-- 1.3.6.1.4.1.10106.3.101291.1.1.147
		dsw3001c01v1NoSigM OBJECT-TYPE
			SYNTAX BitFail
			MAX-ACCESS read-only
			STATUS current
			DESCRIPTION
				"Indicates no SDI signal fail"
		::= { dsw3001c01v1Entry 147 }

		-- 1.3.6.1.4.1.10106.3.101291.1.1.149
		dsw3001c01v1BadFmtM OBJECT-TYPE
			SYNTAX BitFail
			MAX-ACCESS read-only
			STATUS current
			DESCRIPTION
				"Indicates bad SDI format fail"
		::= { dsw3001c01v1Entry 149 }

		-- 1.3.6.1.4.1.10106.3.101291.1.1.151
		dsw3001c01v1EdhErrM OBJECT-TYPE
			SYNTAX BitFail
			MAX-ACCESS read-only
			STATUS current
			DESCRIPTION
				"Indicates EDH error fail"
		::= { dsw3001c01v1Entry 151 }

		-- 1.3.6.1.4.1.10106.3.101291.1.1.153
		dsw3001c01v1EdhPckM OBJECT-TYPE
			SYNTAX BitFail
			MAX-ACCESS read-only
			STATUS current
			DESCRIPTION
				"Indicates no EDH packets presence fail"
		::= { dsw3001c01v1Entry 153 }

		-- 1.3.6.1.4.1.10106.3.101291.1.1.155
		dsw3001c01v1PatternM OBJECT-TYPE
			SYNTAX BitFail
			MAX-ACCESS read-only
			STATUS current
			DESCRIPTION
				"Indicates fixed pattern fail"
		::= { dsw3001c01v1Entry 155 }

		-- 1.3.6.1.4.1.10106.3.101291.1.1.157
		dsw3001c01v1BlackM OBJECT-TYPE
			SYNTAX BitFail
			MAX-ACCESS read-only
			STATUS current
			DESCRIPTION
				"Indicates black pattern fail"
		::= { dsw3001c01v1Entry 157 }

		-- 1.3.6.1.4.1.10106.3.101291.1.1.159
		dsw3001c01v1FreezeM OBJECT-TYPE
			SYNTAX BitFail
			MAX-ACCESS read-only
			STATUS current
			DESCRIPTION
				"Indicates freeze image fail"
		::= { dsw3001c01v1Entry 159 }

		-- 1.3.6.1.4.1.10106.3.101291.1.1.161
		dsw3001c01v1PresM OBJECT-TYPE
			SYNTAX BitFail
			MAX-ACCESS read-only
			STATUS current
			DESCRIPTION
				"Indicates no audio presence fail"
		::= { dsw3001c01v1Entry 161 }

		-- 1.3.6.1.4.1.10106.3.101291.1.1.163
		dsw3001c01v1SilM OBJECT-TYPE
			SYNTAX BitFail
			MAX-ACCESS read-only
			STATUS current
			DESCRIPTION
				"Indicates audio silence fail"
		::= { dsw3001c01v1Entry 163 }

		-- 1.3.6.1.4.1.10106.3.101291.1.1.165
		dsw3001c01v1OvlM OBJECT-TYPE
			SYNTAX BitFail
			MAX-ACCESS read-only
			STATUS current
			DESCRIPTION
				"Indicates audio overload fail"
		::= { dsw3001c01v1Entry 165 }

		-- 1.3.6.1.4.1.10106.3.101291.1.1.167
		dsw3001c01v1AntiphM OBJECT-TYPE
			SYNTAX BitFail
			MAX-ACCESS read-only
			STATUS current
			DESCRIPTION
				"Indicates audio antiphase fail"
		::= { dsw3001c01v1Entry 167 }

		-- 1.3.6.1.4.1.10106.3.101291.1.1.169
		dsw3001c01v1ExtInpR OBJECT-TYPE
			SYNTAX BitFail
			MAX-ACCESS read-only
			STATUS current
			DESCRIPTION
				"Indicates external fail (GPI)"
		::= { dsw3001c01v1Entry 169 }

		-- 1.3.6.1.4.1.10106.3.101291.1.1.171
		dsw3001c01v1NoSigR OBJECT-TYPE
			SYNTAX BitFail
			MAX-ACCESS read-only
			STATUS current
			DESCRIPTION
				"Indicates no SDI signal fail"
		::= { dsw3001c01v1Entry 171 }

		-- 1.3.6.1.4.1.10106.3.101291.1.1.173
		dsw3001c01v1BadFmtR OBJECT-TYPE
			SYNTAX BitFail
			MAX-ACCESS read-only
			STATUS current
			DESCRIPTION
				"Indicates bad SDI format fail"
		::= { dsw3001c01v1Entry 173 }

		-- 1.3.6.1.4.1.10106.3.101291.1.1.175
		dsw3001c01v1EdhErrR OBJECT-TYPE
			SYNTAX BitFail
			MAX-ACCESS read-only
			STATUS current
			DESCRIPTION
				"Indicates EDH error fail"
		::= { dsw3001c01v1Entry 175 }

		-- 1.3.6.1.4.1.10106.3.101291.1.1.177
		dsw3001c01v1EdhPckR OBJECT-TYPE
			SYNTAX BitFail
			MAX-ACCESS read-only
			STATUS current
			DESCRIPTION
				"Indicates no EDH packets presence fail"
		::= { dsw3001c01v1Entry 177 }

		-- 1.3.6.1.4.1.10106.3.101291.1.1.179
		dsw3001c01v1PatternR OBJECT-TYPE
			SYNTAX BitFail
			MAX-ACCESS read-only
			STATUS current
			DESCRIPTION
				"Indicates fixed pattern fail"
		::= { dsw3001c01v1Entry 179 }

		-- 1.3.6.1.4.1.10106.3.101291.1.1.181
		dsw3001c01v1BlackR OBJECT-TYPE
			SYNTAX BitFail
			MAX-ACCESS read-only
			STATUS current
			DESCRIPTION
				"Indicates black pattern fail"
		::= { dsw3001c01v1Entry 181 }

		-- 1.3.6.1.4.1.10106.3.101291.1.1.183
		dsw3001c01v1FreezeR OBJECT-TYPE
			SYNTAX BitFail
			MAX-ACCESS read-only
			STATUS current
			DESCRIPTION
				"Indicates freeze image fail"
		::= { dsw3001c01v1Entry 183 }

		-- 1.3.6.1.4.1.10106.3.101291.1.1.185
		dsw3001c01v1PresR OBJECT-TYPE
			SYNTAX BitFail
			MAX-ACCESS read-only
			STATUS current
			DESCRIPTION
				"Indicates no audio presence fail"
		::= { dsw3001c01v1Entry 185 }

		-- 1.3.6.1.4.1.10106.3.101291.1.1.187
		dsw3001c01v1SilR OBJECT-TYPE
			SYNTAX BitFail
			MAX-ACCESS read-only
			STATUS current
			DESCRIPTION
				"Indicates audio silence fail"
		::= { dsw3001c01v1Entry 187 }

		-- 1.3.6.1.4.1.10106.3.101291.1.1.189
		dsw3001c01v1OvlR OBJECT-TYPE
			SYNTAX BitFail
			MAX-ACCESS read-only
			STATUS current
			DESCRIPTION
				"Indicates audio overload fail"
		::= { dsw3001c01v1Entry 189 }

		-- 1.3.6.1.4.1.10106.3.101291.1.1.191
		dsw3001c01v1AntiphR OBJECT-TYPE
			SYNTAX BitFail
			MAX-ACCESS read-only
			STATUS current
			DESCRIPTION
				"Indicates audio antiphase fail"
		::= { dsw3001c01v1Entry 191 }

		-- 1.3.6.1.4.1.10106.3.278601
		dvb3001c01v1 OBJECT IDENTIFIER ::= { albalaProducts 278601 }

		-- 1.3.6.1.4.1.10106.3.278601.1
		dvb3001c01v1Table  OBJECT-TYPE
			SYNTAX SEQUENCE OF Dvb3001c01v1Entry
			MAX-ACCESS not-accessible
			STATUS current
			DESCRIPTION
				"Module  DVB3001C01V1 Table"
			::= { dvb3001c01v1 1 }

		-- 1.3.6.1.4.1.10106.3.278601.1.1
		dvb3001c01v1Entry  OBJECT-TYPE
			SYNTAX Dvb3001c01v1Entry
			MAX-ACCESS not-accessible
			STATUS current
			DESCRIPTION
				"Module DVB3001C01V1 Entry"
			INDEX { dvb3001c01v1Index }
			::= { dvb3001c01v1Table 1 }

			Dvb3001c01v1Entry ::=
			SEQUENCE {
				dvb3001c01v1Index
				ModuleIndex,
				dvb3001c01v1NoSigA
				BitFail,
				dvb3001c01v1NoSigATrapEnable
				AlarmEnable,
				dvb3001c01v1MaxEqA
				BitFail,
				dvb3001c01v1NoSigB
				BitFail,
				dvb3001c01v1NoSigBTrapEnable
				AlarmEnable,
				dvb3001c01v1MaxEqB
				BitFail,
				dvb3001c01v1DvdMode
				BitDistrib1,
				dvb3001c01v1CableLengthA
				CableLengthX2m,
				dvb3001c01v1CableLengthB
				CableLengthX2m,
				dvb3001c01v1SerialNo
				SerialNo
			 }

		-- 1.3.6.1.4.1.10106.3.101291.1.1.1
		dvb3001c01v1Index OBJECT-TYPE
			SYNTAX ModuleIndex
			MAX-ACCESS read-only
			STATUS current
			DESCRIPTION
				"Index of DVB3001C01V1 Table"
		::= { dvb3001c01v1Entry 1 }

		-- 1.3.6.1.4.1.10106.3.101291.1.1.3
		dvb3001c01v1NoSigA OBJECT-TYPE
			SYNTAX BitFail
			MAX-ACCESS read-only
			STATUS current
			DESCRIPTION
				"Input signal status"
		::= { dvb3001c01v1Entry 3 }

		-- 1.3.6.1.4.1.10106.3.101291.1.1.4
		dvb3001c01v1NoSigATrapEnable OBJECT-TYPE
			SYNTAX AlarmEnable
			MAX-ACCESS read-write
			STATUS current
			DESCRIPTION
				"Input signal status Trap Enable"
		::= { dvb3001c01v1Entry 4 }

		-- 1.3.6.1.4.1.10106.3.101291.1.1.5
		dvb3001c01v1MaxEqA OBJECT-TYPE
			SYNTAX BitFail
			MAX-ACCESS read-only
			STATUS current
			DESCRIPTION
				"Equalizer status"
		::= { dvb3001c01v1Entry 5 }

		-- 1.3.6.1.4.1.10106.3.101291.1.1.7
		dvb3001c01v1NoSigB OBJECT-TYPE
			SYNTAX BitFail
			MAX-ACCESS read-only
			STATUS current
			DESCRIPTION
				"Input signal status"
		::= { dvb3001c01v1Entry 7 }

		-- 1.3.6.1.4.1.10106.3.101291.1.1.8
		dvb3001c01v1NoSigBTrapEnable OBJECT-TYPE
			SYNTAX AlarmEnable
			MAX-ACCESS read-write
			STATUS current
			DESCRIPTION
				"Input signal status Trap Enable"
		::= { dvb3001c01v1Entry 8 }

		-- 1.3.6.1.4.1.10106.3.101291.1.1.9
		dvb3001c01v1MaxEqB OBJECT-TYPE
			SYNTAX BitFail
			MAX-ACCESS read-only
			STATUS current
			DESCRIPTION
				"Equalizer status"
		::= { dvb3001c01v1Entry 9 }

		-- 1.3.6.1.4.1.10106.3.101291.1.1.11
		dvb3001c01v1DvdMode OBJECT-TYPE
			SYNTAX BitDistrib1
			MAX-ACCESS read-only
			STATUS current
			DESCRIPTION
				"Operating mode"
		::= { dvb3001c01v1Entry 11 }

		-- 1.3.6.1.4.1.10106.3.101291.1.1.13
		dvb3001c01v1CableLengthA OBJECT-TYPE
			SYNTAX CableLengthX2m
			MAX-ACCESS read-only
			STATUS current
			DESCRIPTION
				"Equalized cable length"
		::= { dvb3001c01v1Entry 13 }

		-- 1.3.6.1.4.1.10106.3.101291.1.1.15
		dvb3001c01v1CableLengthB OBJECT-TYPE
			SYNTAX CableLengthX2m
			MAX-ACCESS read-only
			STATUS current
			DESCRIPTION
				"Equalized cable length"
		::= { dvb3001c01v1Entry 15 }

		-- 1.3.6.1.4.1.10106.3.101291.1.1.17
		dvb3001c01v1SerialNo OBJECT-TYPE
			SYNTAX SerialNo
			MAX-ACCESS read-only
			STATUS current
			DESCRIPTION
				"Serial number"
		::= { dvb3001c01v1Entry 17 }

		-- 1.3.6.1.4.1.10106.3.282401
		dvm3001c02v1 OBJECT IDENTIFIER ::= { albalaProducts 282401 }

		-- 1.3.6.1.4.1.10106.3.282401.1
		dvm3001c02v1Table  OBJECT-TYPE
			SYNTAX SEQUENCE OF Dvm3001c02v1Entry
			MAX-ACCESS not-accessible
			STATUS current
			DESCRIPTION
				"Module  DVM3001C02V1 Table"
			::= { dvm3001c02v1 1 }

		-- 1.3.6.1.4.1.10106.3.282401.1.1
		dvm3001c02v1Entry  OBJECT-TYPE
			SYNTAX Dvm3001c02v1Entry
			MAX-ACCESS not-accessible
			STATUS current
			DESCRIPTION
				"Module DVM3001C02V1 Entry"
			INDEX { dvm3001c02v1Index }
			::= { dvm3001c02v1Table 1 }

			Dvm3001c02v1Entry ::=
			SEQUENCE {
				dvm3001c02v1Index
				ModuleIndex,
				dvm3001c02v1VbiPassA
				Bit0Bnk1Pas,
				dvm3001c02v1VbiPassB
				Bit0Bnk1Pas,
				dvm3001c02v1ChromaA
				Bit0Off1On,
				dvm3001c02v1ChromaB
				Bit0Off1On,
				dvm3001c02v1LumaFilterA
				Bit0Not1Flt,
				dvm3001c02v1LumaFilterB
				Bit0Not1Flt,
				dvm3001c02v1CustomFilterA
				Bit0Cus1Std,
				dvm3001c02v1CustomFilterB
				Bit0Cus1Std,
				dvm3001c02v1Mode
				Bit0Sin1Dua,
				dvm3001c02v1NoSigA
				BitFail,
				dvm3001c02v1NoSigATrapEnable
				AlarmEnable,
				dvm3001c02v1NoSigB
				BitFail,
				dvm3001c02v1NoSigBTrapEnable
				AlarmEnable,
				dvm3001c02v1MaxEqA
				BitFail,
				dvm3001c02v1MaxEqB
				BitFail,
				dvm3001c02v1UnlockA
				BitFail,
				dvm3001c02v1UnlockATrapEnable
				AlarmEnable,
				dvm3001c02v1UnlockB
				BitFail,
				dvm3001c02v1UnlockBTrapEnable
				AlarmEnable,
				dvm3001c02v1EdhErrorA
				BitFail,
				dvm3001c02v1EdhErrorB
				BitFail,
				dvm3001c02v1EdhPresA
				Bit0No1Yes,
				dvm3001c02v1EdhPresB
				Bit0No1Yes,
				dvm3001c02v1FormatA
				Bit06251525,
				dvm3001c02v1FormatB
				Bit06251525,
				dvm3001c02v1MuteA
				Bit0No1Yes,
				dvm3001c02v1MuteB
				Bit0No1Yes,
				dvm3001c02v1CableLengthA
				Rate1,
				dvm3001c02v1CableLengthB
				Rate1,
				dvm3001c02v1SerialNo
				SerialNo
			 }

		-- 1.3.6.1.4.1.10106.3.101291.1.1.1
		dvm3001c02v1Index OBJECT-TYPE
			SYNTAX ModuleIndex
			MAX-ACCESS read-only
			STATUS current
			DESCRIPTION
				"Index of DVM3001C02V1 Table"
		::= { dvm3001c02v1Entry 1 }

		-- 1.3.6.1.4.1.10106.3.101291.1.1.3
		dvm3001c02v1VbiPassA OBJECT-TYPE
			SYNTAX Bit0Bnk1Pas
			MAX-ACCESS read-write
			STATUS current
			DESCRIPTION
				"Allows selecting if the VBI is blanked"
		::= { dvm3001c02v1Entry 3 }

		-- 1.3.6.1.4.1.10106.3.101291.1.1.5
		dvm3001c02v1VbiPassB OBJECT-TYPE
			SYNTAX Bit0Bnk1Pas
			MAX-ACCESS read-write
			STATUS current
			DESCRIPTION
				"Allows selecting if the VBI is blanked"
		::= { dvm3001c02v1Entry 5 }

		-- 1.3.6.1.4.1.10106.3.101291.1.1.7
		dvm3001c02v1ChromaA OBJECT-TYPE
			SYNTAX Bit0Off1On
			MAX-ACCESS read-write
			STATUS current
			DESCRIPTION
				"Allows disabling chroma"
		::= { dvm3001c02v1Entry 7 }

		-- 1.3.6.1.4.1.10106.3.101291.1.1.9
		dvm3001c02v1ChromaB OBJECT-TYPE
			SYNTAX Bit0Off1On
			MAX-ACCESS read-write
			STATUS current
			DESCRIPTION
				"Allows disabling chroma"
		::= { dvm3001c02v1Entry 9 }

		-- 1.3.6.1.4.1.10106.3.101291.1.1.11
		dvm3001c02v1LumaFilterA OBJECT-TYPE
			SYNTAX Bit0Not1Flt
			MAX-ACCESS read-write
			STATUS current
			DESCRIPTION
				"Allows selecting luminance filter"
		::= { dvm3001c02v1Entry 11 }

		-- 1.3.6.1.4.1.10106.3.101291.1.1.13
		dvm3001c02v1LumaFilterB OBJECT-TYPE
			SYNTAX Bit0Not1Flt
			MAX-ACCESS read-write
			STATUS current
			DESCRIPTION
				"Allows selecting luminance filter"
		::= { dvm3001c02v1Entry 13 }

		-- 1.3.6.1.4.1.10106.3.101291.1.1.15
		dvm3001c02v1CustomFilterA OBJECT-TYPE
			SYNTAX Bit0Cus1Std
			MAX-ACCESS read-write
			STATUS current
			DESCRIPTION
				"Allows selecting a custom luminance filter"
		::= { dvm3001c02v1Entry 15 }

		-- 1.3.6.1.4.1.10106.3.101291.1.1.17
		dvm3001c02v1CustomFilterB OBJECT-TYPE
			SYNTAX Bit0Cus1Std
			MAX-ACCESS read-write
			STATUS current
			DESCRIPTION
				"Allows selecting a custom luminance filter"
		::= { dvm3001c02v1Entry 17 }

		-- 1.3.6.1.4.1.10106.3.101291.1.1.19
		dvm3001c02v1Mode OBJECT-TYPE
			SYNTAX Bit0Sin1Dua
			MAX-ACCESS read-write
			STATUS current
			DESCRIPTION
				"Allows selecting module operating mode"
		::= { dvm3001c02v1Entry 19 }

		-- 1.3.6.1.4.1.10106.3.101291.1.1.21
		dvm3001c02v1NoSigA OBJECT-TYPE
			SYNTAX BitFail
			MAX-ACCESS read-only
			STATUS current
			DESCRIPTION
				"Input signal status"
		::= { dvm3001c02v1Entry 21 }

		-- 1.3.6.1.4.1.10106.3.101291.1.1.22
		dvm3001c02v1NoSigATrapEnable OBJECT-TYPE
			SYNTAX AlarmEnable
			MAX-ACCESS read-write
			STATUS current
			DESCRIPTION
				"Input signal status Trap Enable"
		::= { dvm3001c02v1Entry 22 }

		-- 1.3.6.1.4.1.10106.3.101291.1.1.23
		dvm3001c02v1NoSigB OBJECT-TYPE
			SYNTAX BitFail
			MAX-ACCESS read-only
			STATUS current
			DESCRIPTION
				"Input signal status"
		::= { dvm3001c02v1Entry 23 }

		-- 1.3.6.1.4.1.10106.3.101291.1.1.24
		dvm3001c02v1NoSigBTrapEnable OBJECT-TYPE
			SYNTAX AlarmEnable
			MAX-ACCESS read-write
			STATUS current
			DESCRIPTION
				"Input signal status Trap Enable"
		::= { dvm3001c02v1Entry 24 }

		-- 1.3.6.1.4.1.10106.3.101291.1.1.25
		dvm3001c02v1MaxEqA OBJECT-TYPE
			SYNTAX BitFail
			MAX-ACCESS read-only
			STATUS current
			DESCRIPTION
				"Indicates maximum equalization"
		::= { dvm3001c02v1Entry 25 }

		-- 1.3.6.1.4.1.10106.3.101291.1.1.27
		dvm3001c02v1MaxEqB OBJECT-TYPE
			SYNTAX BitFail
			MAX-ACCESS read-only
			STATUS current
			DESCRIPTION
				"Indicates maximum equalization"
		::= { dvm3001c02v1Entry 27 }

		-- 1.3.6.1.4.1.10106.3.101291.1.1.29
		dvm3001c02v1UnlockA OBJECT-TYPE
			SYNTAX BitFail
			MAX-ACCESS read-only
			STATUS current
			DESCRIPTION
				"Indicates signal unlock fail"
		::= { dvm3001c02v1Entry 29 }

		-- 1.3.6.1.4.1.10106.3.101291.1.1.30
		dvm3001c02v1UnlockATrapEnable OBJECT-TYPE
			SYNTAX AlarmEnable
			MAX-ACCESS read-write
			STATUS current
			DESCRIPTION
				"Indicates signal unlock fail Trap Enable"
		::= { dvm3001c02v1Entry 30 }

		-- 1.3.6.1.4.1.10106.3.101291.1.1.31
		dvm3001c02v1UnlockB OBJECT-TYPE
			SYNTAX BitFail
			MAX-ACCESS read-only
			STATUS current
			DESCRIPTION
				"Indicates signal unlock fail"
		::= { dvm3001c02v1Entry 31 }

		-- 1.3.6.1.4.1.10106.3.101291.1.1.32
		dvm3001c02v1UnlockBTrapEnable OBJECT-TYPE
			SYNTAX AlarmEnable
			MAX-ACCESS read-write
			STATUS current
			DESCRIPTION
				"Indicates signal unlock fail Trap Enable"
		::= { dvm3001c02v1Entry 32 }

		-- 1.3.6.1.4.1.10106.3.101291.1.1.33
		dvm3001c02v1EdhErrorA OBJECT-TYPE
			SYNTAX BitFail
			MAX-ACCESS read-only
			STATUS current
			DESCRIPTION
				"EDH status"
		::= { dvm3001c02v1Entry 33 }

		-- 1.3.6.1.4.1.10106.3.101291.1.1.35
		dvm3001c02v1EdhErrorB OBJECT-TYPE
			SYNTAX BitFail
			MAX-ACCESS read-only
			STATUS current
			DESCRIPTION
				"EDH status"
		::= { dvm3001c02v1Entry 35 }

		-- 1.3.6.1.4.1.10106.3.101291.1.1.37
		dvm3001c02v1EdhPresA OBJECT-TYPE
			SYNTAX Bit0No1Yes
			MAX-ACCESS read-only
			STATUS current
			DESCRIPTION
				"EDH packet presence"
		::= { dvm3001c02v1Entry 37 }

		-- 1.3.6.1.4.1.10106.3.101291.1.1.39
		dvm3001c02v1EdhPresB OBJECT-TYPE
			SYNTAX Bit0No1Yes
			MAX-ACCESS read-only
			STATUS current
			DESCRIPTION
				"EDH packet presence"
		::= { dvm3001c02v1Entry 39 }

		-- 1.3.6.1.4.1.10106.3.101291.1.1.41
		dvm3001c02v1FormatA OBJECT-TYPE
			SYNTAX Bit06251525
			MAX-ACCESS read-only
			STATUS current
			DESCRIPTION
				"Format"
		::= { dvm3001c02v1Entry 41 }

		-- 1.3.6.1.4.1.10106.3.101291.1.1.43
		dvm3001c02v1FormatB OBJECT-TYPE
			SYNTAX Bit06251525
			MAX-ACCESS read-only
			STATUS current
			DESCRIPTION
				"Format"
		::= { dvm3001c02v1Entry 43 }

		-- 1.3.6.1.4.1.10106.3.101291.1.1.45
		dvm3001c02v1MuteA OBJECT-TYPE
			SYNTAX Bit0No1Yes
			MAX-ACCESS read-only
			STATUS current
			DESCRIPTION
				"Output muted"
		::= { dvm3001c02v1Entry 45 }

		-- 1.3.6.1.4.1.10106.3.101291.1.1.47
		dvm3001c02v1MuteB OBJECT-TYPE
			SYNTAX Bit0No1Yes
			MAX-ACCESS read-only
			STATUS current
			DESCRIPTION
				"Output muted"
		::= { dvm3001c02v1Entry 47 }

		-- 1.3.6.1.4.1.10106.3.101291.1.1.49
		dvm3001c02v1CableLengthA OBJECT-TYPE
			SYNTAX Rate1
			MAX-ACCESS read-only
			STATUS current
			DESCRIPTION
				"Equalization level refered to maximun"
		::= { dvm3001c02v1Entry 49 }

		-- 1.3.6.1.4.1.10106.3.101291.1.1.51
		dvm3001c02v1CableLengthB OBJECT-TYPE
			SYNTAX Rate1
			MAX-ACCESS read-only
			STATUS current
			DESCRIPTION
				"Equalization level refered to maximun"
		::= { dvm3001c02v1Entry 51 }

		-- 1.3.6.1.4.1.10106.3.101291.1.1.53
		dvm3001c02v1SerialNo OBJECT-TYPE
			SYNTAX SerialNo
			MAX-ACCESS read-only
			STATUS current
			DESCRIPTION
				"Serial number"
		::= { dvm3001c02v1Entry 53 }

		-- 1.3.6.1.4.1.10106.3.283901
		dvb3001c02v1 OBJECT IDENTIFIER ::= { albalaProducts 283901 }

		-- 1.3.6.1.4.1.10106.3.283901.1
		dvb3001c02v1Table  OBJECT-TYPE
			SYNTAX SEQUENCE OF Dvb3001c02v1Entry
			MAX-ACCESS not-accessible
			STATUS current
			DESCRIPTION
				"Module  DVB3001C02V1 Table"
			::= { dvb3001c02v1 1 }

		-- 1.3.6.1.4.1.10106.3.283901.1.1
		dvb3001c02v1Entry  OBJECT-TYPE
			SYNTAX Dvb3001c02v1Entry
			MAX-ACCESS not-accessible
			STATUS current
			DESCRIPTION
				"Module DVB3001C02V1 Entry"
			INDEX { dvb3001c02v1Index }
			::= { dvb3001c02v1Table 1 }

			Dvb3001c02v1Entry ::=
			SEQUENCE {
				dvb3001c02v1Index
				ModuleIndex,
				dvb3001c02v1NoSigA
				BitFail,
				dvb3001c02v1NoSigATrapEnable
				AlarmEnable,
				dvb3001c02v1MaxEqA
				BitFail,
				dvb3001c02v1NoSigB
				BitFail,
				dvb3001c02v1NoSigBTrapEnable
				AlarmEnable,
				dvb3001c02v1MaxEqB
				BitFail,
				dvb3001c02v1DvdMode
				BitDistrib1,
				dvb3001c02v1CableLengthA
				CableLengthX2m,
				dvb3001c02v1CableLengthB
				CableLengthX2m,
				dvb3001c02v1SerialNo
				SerialNo
			 }

		-- 1.3.6.1.4.1.10106.3.101291.1.1.1
		dvb3001c02v1Index OBJECT-TYPE
			SYNTAX ModuleIndex
			MAX-ACCESS read-only
			STATUS current
			DESCRIPTION
				"Index of DVB3001C02V1 Table"
		::= { dvb3001c02v1Entry 1 }

		-- 1.3.6.1.4.1.10106.3.101291.1.1.3
		dvb3001c02v1NoSigA OBJECT-TYPE
			SYNTAX BitFail
			MAX-ACCESS read-only
			STATUS current
			DESCRIPTION
				"Input signal status"
		::= { dvb3001c02v1Entry 3 }

		-- 1.3.6.1.4.1.10106.3.101291.1.1.4
		dvb3001c02v1NoSigATrapEnable OBJECT-TYPE
			SYNTAX AlarmEnable
			MAX-ACCESS read-write
			STATUS current
			DESCRIPTION
				"Input signal status Trap Enable"
		::= { dvb3001c02v1Entry 4 }

		-- 1.3.6.1.4.1.10106.3.101291.1.1.5
		dvb3001c02v1MaxEqA OBJECT-TYPE
			SYNTAX BitFail
			MAX-ACCESS read-only
			STATUS current
			DESCRIPTION
				"Equalizer status"
		::= { dvb3001c02v1Entry 5 }

		-- 1.3.6.1.4.1.10106.3.101291.1.1.7
		dvb3001c02v1NoSigB OBJECT-TYPE
			SYNTAX BitFail
			MAX-ACCESS read-only
			STATUS current
			DESCRIPTION
				"Input signal status"
		::= { dvb3001c02v1Entry 7 }

		-- 1.3.6.1.4.1.10106.3.101291.1.1.8
		dvb3001c02v1NoSigBTrapEnable OBJECT-TYPE
			SYNTAX AlarmEnable
			MAX-ACCESS read-write
			STATUS current
			DESCRIPTION
				"Input signal status Trap Enable"
		::= { dvb3001c02v1Entry 8 }

		-- 1.3.6.1.4.1.10106.3.101291.1.1.9
		dvb3001c02v1MaxEqB OBJECT-TYPE
			SYNTAX BitFail
			MAX-ACCESS read-only
			STATUS current
			DESCRIPTION
				"Equalizer status"
		::= { dvb3001c02v1Entry 9 }

		-- 1.3.6.1.4.1.10106.3.101291.1.1.11
		dvb3001c02v1DvdMode OBJECT-TYPE
			SYNTAX BitDistrib1
			MAX-ACCESS read-only
			STATUS current
			DESCRIPTION
				"Operating mode"
		::= { dvb3001c02v1Entry 11 }

		-- 1.3.6.1.4.1.10106.3.101291.1.1.13
		dvb3001c02v1CableLengthA OBJECT-TYPE
			SYNTAX CableLengthX2m
			MAX-ACCESS read-only
			STATUS current
			DESCRIPTION
				"Equalized cable length"
		::= { dvb3001c02v1Entry 13 }

		-- 1.3.6.1.4.1.10106.3.101291.1.1.15
		dvb3001c02v1CableLengthB OBJECT-TYPE
			SYNTAX CableLengthX2m
			MAX-ACCESS read-only
			STATUS current
			DESCRIPTION
				"Equalized cable length"
		::= { dvb3001c02v1Entry 15 }

		-- 1.3.6.1.4.1.10106.3.101291.1.1.17
		dvb3001c02v1SerialNo OBJECT-TYPE
			SYNTAX SerialNo
			MAX-ACCESS read-only
			STATUS current
			DESCRIPTION
				"Serial number"
		::= { dvb3001c02v1Entry 17 }

		-- 1.3.6.1.4.1.10106.3.286201
		gps3002c01v1 OBJECT IDENTIFIER ::= { albalaProducts 286201 }

		-- 1.3.6.1.4.1.10106.3.286201.1
		gps3002c01v1Table  OBJECT-TYPE
			SYNTAX SEQUENCE OF Gps3002c01v1Entry
			MAX-ACCESS not-accessible
			STATUS current
			DESCRIPTION
				"Module  GPS3002C01V1 Table"
			::= { gps3002c01v1 1 }

		-- 1.3.6.1.4.1.10106.3.286201.1.1
		gps3002c01v1Entry  OBJECT-TYPE
			SYNTAX Gps3002c01v1Entry
			MAX-ACCESS not-accessible
			STATUS current
			DESCRIPTION
				"Module GPS3002C01V1 Entry"
			INDEX { gps3002c01v1Index }
			::= { gps3002c01v1Table 1 }

			Gps3002c01v1Entry ::=
			SEQUENCE {
				gps3002c01v1Index
				ModuleIndex,
				gps3002c01v1Holdover
				Bit0Dis1Ena,
				gps3002c01v1RedundanceMode
				ChgOverMode3,
				gps3002c01v1RedundanceModeTrapEnable
				AlarmEnable,
				gps3002c01v1CableDelay
				DelayX2Ns,
				gps3002c01v1HoldoverStat
				Bit0Trk1Hol,
				gps3002c01v1HoldoverStatTrapEnable
				AlarmEnable,
				gps3002c01v1MaintenanceFail
				Bit0No1Yes,
				gps3002c01v1MaintenanceFailTrapEnable
				AlarmEnable,
				gps3002c01v1OutputsMuted
				BitFail,
				gps3002c01v1OutputsMutedTrapEnable
				AlarmEnable,
				gps3002c01v11ppsDisable
				BitFail,
				gps3002c01v11ppsDisableTrapEnable
				AlarmEnable,
				gps3002c01v1AdquisitionStat
				GpsAdqStat2,
				gps3002c01v1SatRxStat
				GpsSatRxStat,
				gps3002c01v1AntenaStat
				GpsAntenaStat,
				gps3002c01v1AntenaStatTrapEnable
				AlarmEnable,
				gps3002c01v1SatNoFail
				BitFail,
				gps3002c01v1GpsSiteSurv
				Bit0No1Yes,
				gps3002c01v1GpsTrackSats
				GpsSatellites,
				gps3002c01v1GpsVisibleSats
				GpsSatellites,
				gps3002c01v1GpsSignalLevel
				LevelDbHz,
				gps3002c01v1HoldoverTime
				GpsHoldovrTime,
				gps3002c01v1FreqDriftEst
				GpsFrqDrftEst,
				gps3002c01v1PhaseDriftEst
				GpsPhsDrftEst,
				gps3002c01v1SerialNo
				SerialNo
			 }

		-- 1.3.6.1.4.1.10106.3.101291.1.1.1
		gps3002c01v1Index OBJECT-TYPE
			SYNTAX ModuleIndex
			MAX-ACCESS read-only
			STATUS current
			DESCRIPTION
				"Index of GPS3002C01V1 Table"
		::= { gps3002c01v1Entry 1 }

		-- 1.3.6.1.4.1.10106.3.101291.1.1.3
		gps3002c01v1Holdover OBJECT-TYPE
			SYNTAX Bit0Dis1Ena
			MAX-ACCESS read-write
			STATUS current
			DESCRIPTION
				"Allows setting the module in the holdover mode"
		::= { gps3002c01v1Entry 3 }

		-- 1.3.6.1.4.1.10106.3.101291.1.1.5
		gps3002c01v1RedundanceMode OBJECT-TYPE
			SYNTAX ChgOverMode3
			MAX-ACCESS read-write
			STATUS current
			DESCRIPTION
				"Allows selecting the redundance mode"
		::= { gps3002c01v1Entry 5 }

		-- 1.3.6.1.4.1.10106.3.101291.1.1.6
		gps3002c01v1RedundanceModeTrapEnable OBJECT-TYPE
			SYNTAX AlarmEnable
			MAX-ACCESS read-write
			STATUS current
			DESCRIPTION
				"Allows selecting the redundance mode Trap Enable"
		::= { gps3002c01v1Entry 6 }

		-- 1.3.6.1.4.1.10106.3.101291.1.1.7
		gps3002c01v1CableDelay OBJECT-TYPE
			SYNTAX DelayX2Ns
			MAX-ACCESS read-write
			STATUS current
			DESCRIPTION
				"Allows compensating the antenna cable delay"
		::= { gps3002c01v1Entry 7 }

		-- 1.3.6.1.4.1.10106.3.101291.1.1.9
		gps3002c01v1HoldoverStat OBJECT-TYPE
			SYNTAX Bit0Trk1Hol
			MAX-ACCESS read-only
			STATUS current
			DESCRIPTION
				"Indicates if the module is locked to GPS or to reference or it is in holdover mode"
		::= { gps3002c01v1Entry 9 }

		-- 1.3.6.1.4.1.10106.3.101291.1.1.10
		gps3002c01v1HoldoverStatTrapEnable OBJECT-TYPE
			SYNTAX AlarmEnable
			MAX-ACCESS read-write
			STATUS current
			DESCRIPTION
				"Indicates if the module is locked to GPS or to reference or it is in holdover mode Trap Enable"
		::= { gps3002c01v1Entry 10 }

		-- 1.3.6.1.4.1.10106.3.101291.1.1.11
		gps3002c01v1MaintenanceFail OBJECT-TYPE
			SYNTAX Bit0No1Yes
			MAX-ACCESS read-only
			STATUS current
			DESCRIPTION
				"Indicates that a service operation is required"
		::= { gps3002c01v1Entry 11 }

		-- 1.3.6.1.4.1.10106.3.101291.1.1.12
		gps3002c01v1MaintenanceFailTrapEnable OBJECT-TYPE
			SYNTAX AlarmEnable
			MAX-ACCESS read-write
			STATUS current
			DESCRIPTION
				"Indicates that a service operation is required Trap Enable"
		::= { gps3002c01v1Entry 12 }

		-- 1.3.6.1.4.1.10106.3.101291.1.1.13
		gps3002c01v1OutputsMuted OBJECT-TYPE
			SYNTAX BitFail
			MAX-ACCESS read-only
			STATUS current
			DESCRIPTION
				"Indicates f the module outputs are disabled (reserve module)"
		::= { gps3002c01v1Entry 13 }

		-- 1.3.6.1.4.1.10106.3.101291.1.1.14
		gps3002c01v1OutputsMutedTrapEnable OBJECT-TYPE
			SYNTAX AlarmEnable
			MAX-ACCESS read-write
			STATUS current
			DESCRIPTION
				"Indicates f the module outputs are disabled (reserve module) Trap Enable"
		::= { gps3002c01v1Entry 14 }

		-- 1.3.6.1.4.1.10106.3.101291.1.1.15
		gps3002c01v11ppsDisable OBJECT-TYPE
			SYNTAX BitFail
			MAX-ACCESS read-only
			STATUS current
			DESCRIPTION
				"Indicates if the 1PPS output is muted"
		::= { gps3002c01v1Entry 15 }

		-- 1.3.6.1.4.1.10106.3.101291.1.1.16
		gps3002c01v11ppsDisableTrapEnable OBJECT-TYPE
			SYNTAX AlarmEnable
			MAX-ACCESS read-write
			STATUS current
			DESCRIPTION
				"Indicates if the 1PPS output is muted Trap Enable"
		::= { gps3002c01v1Entry 16 }

		-- 1.3.6.1.4.1.10106.3.101291.1.1.17
		gps3002c01v1AdquisitionStat OBJECT-TYPE
			SYNTAX GpsAdqStat2
			MAX-ACCESS read-only
			STATUS current
			DESCRIPTION
				"GPS3002 module adquisition status"
		::= { gps3002c01v1Entry 17 }

		-- 1.3.6.1.4.1.10106.3.101291.1.1.19
		gps3002c01v1SatRxStat OBJECT-TYPE
			SYNTAX GpsSatRxStat
			MAX-ACCESS read-only
			STATUS current
			DESCRIPTION
				"GPS receiver module satellite tracking status"
		::= { gps3002c01v1Entry 19 }

		-- 1.3.6.1.4.1.10106.3.101291.1.1.21
		gps3002c01v1AntenaStat OBJECT-TYPE
			SYNTAX GpsAntenaStat
			MAX-ACCESS read-only
			STATUS current
			DESCRIPTION
				"Antenna connection status"
		::= { gps3002c01v1Entry 21 }

		-- 1.3.6.1.4.1.10106.3.101291.1.1.22
		gps3002c01v1AntenaStatTrapEnable OBJECT-TYPE
			SYNTAX AlarmEnable
			MAX-ACCESS read-write
			STATUS current
			DESCRIPTION
				"Antenna connection status Trap Enable"
		::= { gps3002c01v1Entry 22 }

		-- 1.3.6.1.4.1.10106.3.101291.1.1.23
		gps3002c01v1SatNoFail OBJECT-TYPE
			SYNTAX BitFail
			MAX-ACCESS read-only
			STATUS current
			DESCRIPTION
				"Indicates that the number of visible satellites is low"
		::= { gps3002c01v1Entry 23 }

		-- 1.3.6.1.4.1.10106.3.101291.1.1.25
		gps3002c01v1GpsSiteSurv OBJECT-TYPE
			SYNTAX Bit0No1Yes
			MAX-ACCESS read-only
			STATUS current
			DESCRIPTION
				"Indicates that GPS receiver module is in site survey mode"
		::= { gps3002c01v1Entry 25 }

		-- 1.3.6.1.4.1.10106.3.101291.1.1.27
		gps3002c01v1GpsTrackSats OBJECT-TYPE
			SYNTAX GpsSatellites
			MAX-ACCESS read-only
			STATUS current
			DESCRIPTION
				"Number of GPS tracking satellites"
		::= { gps3002c01v1Entry 27 }

		-- 1.3.6.1.4.1.10106.3.101291.1.1.29
		gps3002c01v1GpsVisibleSats OBJECT-TYPE
			SYNTAX GpsSatellites
			MAX-ACCESS read-only
			STATUS current
			DESCRIPTION
				"Number of GPS visible satellites"
		::= { gps3002c01v1Entry 29 }

		-- 1.3.6.1.4.1.10106.3.101291.1.1.31
		gps3002c01v1GpsSignalLevel OBJECT-TYPE
			SYNTAX LevelDbHz
			MAX-ACCESS read-only
			STATUS current
			DESCRIPTION
				"Estimated carrier to noise ratio for the best satellite in tracking"
		::= { gps3002c01v1Entry 31 }

		-- 1.3.6.1.4.1.10106.3.101291.1.1.33
		gps3002c01v1HoldoverTime OBJECT-TYPE
			SYNTAX GpsHoldovrTime
			MAX-ACCESS read-only
			STATUS current
			DESCRIPTION
				"Holdover time"
		::= { gps3002c01v1Entry 33 }

		-- 1.3.6.1.4.1.10106.3.101291.1.1.35
		gps3002c01v1FreqDriftEst OBJECT-TYPE
			SYNTAX GpsFrqDrftEst
			MAX-ACCESS read-only
			STATUS current
			DESCRIPTION
				"Frequency drift estimation"
		::= { gps3002c01v1Entry 35 }

		-- 1.3.6.1.4.1.10106.3.101291.1.1.37
		gps3002c01v1PhaseDriftEst OBJECT-TYPE
			SYNTAX GpsPhsDrftEst
			MAX-ACCESS read-only
			STATUS current
			DESCRIPTION
				"Phase drift estimation"
		::= { gps3002c01v1Entry 37 }

		-- 1.3.6.1.4.1.10106.3.101291.1.1.39
		gps3002c01v1SerialNo OBJECT-TYPE
			SYNTAX SerialNo
			MAX-ACCESS read-only
			STATUS current
			DESCRIPTION
				"Serial number"
		::= { gps3002c01v1Entry 39 }

		-- 1.3.6.1.4.1.10106.3.290701
		gps3002c03v1 OBJECT IDENTIFIER ::= { albalaProducts 290701 }

		-- 1.3.6.1.4.1.10106.3.290701.1
		gps3002c03v1Table  OBJECT-TYPE
			SYNTAX SEQUENCE OF Gps3002c03v1Entry
			MAX-ACCESS not-accessible
			STATUS current
			DESCRIPTION
				"Module  GPS3002C03V1 Table"
			::= { gps3002c03v1 1 }

		-- 1.3.6.1.4.1.10106.3.290701.1.1
		gps3002c03v1Entry  OBJECT-TYPE
			SYNTAX Gps3002c03v1Entry
			MAX-ACCESS not-accessible
			STATUS current
			DESCRIPTION
				"Module GPS3002C03V1 Entry"
			INDEX { gps3002c03v1Index }
			::= { gps3002c03v1Table 1 }

			Gps3002c03v1Entry ::=
			SEQUENCE {
				gps3002c03v1Index
				ModuleIndex,
				gps3002c03v1Holdover
				Bit0Dis1Ena,
				gps3002c03v1RedundanceMode
				ChgOverMode3,
				gps3002c03v1RedundanceModeTrapEnable
				AlarmEnable,
				gps3002c03v1CableDelay
				DelayX2Ns,
				gps3002c03v1HoldoverStat
				Bit0Trk1Hol,
				gps3002c03v1HoldoverStatTrapEnable
				AlarmEnable,
				gps3002c03v1MaintenanceFail
				Bit0No1Yes,
				gps3002c03v1MaintenanceFailTrapEnable
				AlarmEnable,
				gps3002c03v1OutputsMuted
				BitFail,
				gps3002c03v1OutputsMutedTrapEnable
				AlarmEnable,
				gps3002c03v11ppsDisable
				BitFail,
				gps3002c03v11ppsDisableTrapEnable
				AlarmEnable,
				gps3002c03v1AdquisitionStat
				GpsAdqStat2,
				gps3002c03v1SatRxStat
				GpsSatRxStat,
				gps3002c03v1AntenaStat
				GpsAntenaStat,
				gps3002c03v1AntenaStatTrapEnable
				AlarmEnable,
				gps3002c03v1SatNoFail
				BitFail,
				gps3002c03v1GpsSiteSurv
				Bit0No1Yes,
				gps3002c03v1GpsTrackSats
				GpsSatellites,
				gps3002c03v1GpsVisibleSats
				GpsSatellites,
				gps3002c03v1GpsSignalLevel
				LevelDbHz,
				gps3002c03v1HoldoverTime
				GpsHoldovrTime,
				gps3002c03v1FreqDriftEst
				GpsFrqDrftEst,
				gps3002c03v1PhaseDriftEst
				GpsPhsDrftEst,
				gps3002c03v1SerialNo
				SerialNo
			 }

		-- 1.3.6.1.4.1.10106.3.101291.1.1.1
		gps3002c03v1Index OBJECT-TYPE
			SYNTAX ModuleIndex
			MAX-ACCESS read-only
			STATUS current
			DESCRIPTION
				"Index of GPS3002C03V1 Table"
		::= { gps3002c03v1Entry 1 }

		-- 1.3.6.1.4.1.10106.3.101291.1.1.3
		gps3002c03v1Holdover OBJECT-TYPE
			SYNTAX Bit0Dis1Ena
			MAX-ACCESS read-write
			STATUS current
			DESCRIPTION
				"Allows setting the module in the holdover mode"
		::= { gps3002c03v1Entry 3 }

		-- 1.3.6.1.4.1.10106.3.101291.1.1.5
		gps3002c03v1RedundanceMode OBJECT-TYPE
			SYNTAX ChgOverMode3
			MAX-ACCESS read-write
			STATUS current
			DESCRIPTION
				"Allows selecting the redundance mode"
		::= { gps3002c03v1Entry 5 }

		-- 1.3.6.1.4.1.10106.3.101291.1.1.6
		gps3002c03v1RedundanceModeTrapEnable OBJECT-TYPE
			SYNTAX AlarmEnable
			MAX-ACCESS read-write
			STATUS current
			DESCRIPTION
				"Allows selecting the redundance mode Trap Enable"
		::= { gps3002c03v1Entry 6 }

		-- 1.3.6.1.4.1.10106.3.101291.1.1.7
		gps3002c03v1CableDelay OBJECT-TYPE
			SYNTAX DelayX2Ns
			MAX-ACCESS read-write
			STATUS current
			DESCRIPTION
				"Allows compensating the antenna cable delay"
		::= { gps3002c03v1Entry 7 }

		-- 1.3.6.1.4.1.10106.3.101291.1.1.9
		gps3002c03v1HoldoverStat OBJECT-TYPE
			SYNTAX Bit0Trk1Hol
			MAX-ACCESS read-only
			STATUS current
			DESCRIPTION
				"Indicates if the module is locked to GPS or to reference or it is in holdover mode"
		::= { gps3002c03v1Entry 9 }

		-- 1.3.6.1.4.1.10106.3.101291.1.1.10
		gps3002c03v1HoldoverStatTrapEnable OBJECT-TYPE
			SYNTAX AlarmEnable
			MAX-ACCESS read-write
			STATUS current
			DESCRIPTION
				"Indicates if the module is locked to GPS or to reference or it is in holdover mode Trap Enable"
		::= { gps3002c03v1Entry 10 }

		-- 1.3.6.1.4.1.10106.3.101291.1.1.11
		gps3002c03v1MaintenanceFail OBJECT-TYPE
			SYNTAX Bit0No1Yes
			MAX-ACCESS read-only
			STATUS current
			DESCRIPTION
				"Indicates that a service operation is required"
		::= { gps3002c03v1Entry 11 }

		-- 1.3.6.1.4.1.10106.3.101291.1.1.12
		gps3002c03v1MaintenanceFailTrapEnable OBJECT-TYPE
			SYNTAX AlarmEnable
			MAX-ACCESS read-write
			STATUS current
			DESCRIPTION
				"Indicates that a service operation is required Trap Enable"
		::= { gps3002c03v1Entry 12 }

		-- 1.3.6.1.4.1.10106.3.101291.1.1.13
		gps3002c03v1OutputsMuted OBJECT-TYPE
			SYNTAX BitFail
			MAX-ACCESS read-only
			STATUS current
			DESCRIPTION
				"Indicates f the module outputs are disabled (reserve module)"
		::= { gps3002c03v1Entry 13 }

		-- 1.3.6.1.4.1.10106.3.101291.1.1.14
		gps3002c03v1OutputsMutedTrapEnable OBJECT-TYPE
			SYNTAX AlarmEnable
			MAX-ACCESS read-write
			STATUS current
			DESCRIPTION
				"Indicates f the module outputs are disabled (reserve module) Trap Enable"
		::= { gps3002c03v1Entry 14 }

		-- 1.3.6.1.4.1.10106.3.101291.1.1.15
		gps3002c03v11ppsDisable OBJECT-TYPE
			SYNTAX BitFail
			MAX-ACCESS read-only
			STATUS current
			DESCRIPTION
				"Indicates if the 1PPS output is muted"
		::= { gps3002c03v1Entry 15 }

		-- 1.3.6.1.4.1.10106.3.101291.1.1.16
		gps3002c03v11ppsDisableTrapEnable OBJECT-TYPE
			SYNTAX AlarmEnable
			MAX-ACCESS read-write
			STATUS current
			DESCRIPTION
				"Indicates if the 1PPS output is muted Trap Enable"
		::= { gps3002c03v1Entry 16 }

		-- 1.3.6.1.4.1.10106.3.101291.1.1.17
		gps3002c03v1AdquisitionStat OBJECT-TYPE
			SYNTAX GpsAdqStat2
			MAX-ACCESS read-only
			STATUS current
			DESCRIPTION
				"GPS3002 module adquisition status"
		::= { gps3002c03v1Entry 17 }

		-- 1.3.6.1.4.1.10106.3.101291.1.1.19
		gps3002c03v1SatRxStat OBJECT-TYPE
			SYNTAX GpsSatRxStat
			MAX-ACCESS read-only
			STATUS current
			DESCRIPTION
				"GPS receiver module satellite tracking status"
		::= { gps3002c03v1Entry 19 }

		-- 1.3.6.1.4.1.10106.3.101291.1.1.21
		gps3002c03v1AntenaStat OBJECT-TYPE
			SYNTAX GpsAntenaStat
			MAX-ACCESS read-only
			STATUS current
			DESCRIPTION
				"Antenna connection status"
		::= { gps3002c03v1Entry 21 }

		-- 1.3.6.1.4.1.10106.3.101291.1.1.22
		gps3002c03v1AntenaStatTrapEnable OBJECT-TYPE
			SYNTAX AlarmEnable
			MAX-ACCESS read-write
			STATUS current
			DESCRIPTION
				"Antenna connection status Trap Enable"
		::= { gps3002c03v1Entry 22 }

		-- 1.3.6.1.4.1.10106.3.101291.1.1.23
		gps3002c03v1SatNoFail OBJECT-TYPE
			SYNTAX BitFail
			MAX-ACCESS read-only
			STATUS current
			DESCRIPTION
				"Indicates that the number of visible satellites is low"
		::= { gps3002c03v1Entry 23 }

		-- 1.3.6.1.4.1.10106.3.101291.1.1.25
		gps3002c03v1GpsSiteSurv OBJECT-TYPE
			SYNTAX Bit0No1Yes
			MAX-ACCESS read-only
			STATUS current
			DESCRIPTION
				"Indicates that GPS receiver module is in site survey mode"
		::= { gps3002c03v1Entry 25 }

		-- 1.3.6.1.4.1.10106.3.101291.1.1.27
		gps3002c03v1GpsTrackSats OBJECT-TYPE
			SYNTAX GpsSatellites
			MAX-ACCESS read-only
			STATUS current
			DESCRIPTION
				"Number of GPS tracking satellites"
		::= { gps3002c03v1Entry 27 }

		-- 1.3.6.1.4.1.10106.3.101291.1.1.29
		gps3002c03v1GpsVisibleSats OBJECT-TYPE
			SYNTAX GpsSatellites
			MAX-ACCESS read-only
			STATUS current
			DESCRIPTION
				"Number of GPS visible satellites"
		::= { gps3002c03v1Entry 29 }

		-- 1.3.6.1.4.1.10106.3.101291.1.1.31
		gps3002c03v1GpsSignalLevel OBJECT-TYPE
			SYNTAX LevelDbHz
			MAX-ACCESS read-only
			STATUS current
			DESCRIPTION
				"Estimated carrier to noise ratio for the best satellite in tracking"
		::= { gps3002c03v1Entry 31 }

		-- 1.3.6.1.4.1.10106.3.101291.1.1.33
		gps3002c03v1HoldoverTime OBJECT-TYPE
			SYNTAX GpsHoldovrTime
			MAX-ACCESS read-only
			STATUS current
			DESCRIPTION
				"Holdover time"
		::= { gps3002c03v1Entry 33 }

		-- 1.3.6.1.4.1.10106.3.101291.1.1.35
		gps3002c03v1FreqDriftEst OBJECT-TYPE
			SYNTAX GpsFrqDrftEst
			MAX-ACCESS read-only
			STATUS current
			DESCRIPTION
				"Frequency drift estimation"
		::= { gps3002c03v1Entry 35 }

		-- 1.3.6.1.4.1.10106.3.101291.1.1.37
		gps3002c03v1PhaseDriftEst OBJECT-TYPE
			SYNTAX GpsPhsDrftEst
			MAX-ACCESS read-only
			STATUS current
			DESCRIPTION
				"Phase drift estimation"
		::= { gps3002c03v1Entry 37 }

		-- 1.3.6.1.4.1.10106.3.101291.1.1.39
		gps3002c03v1SerialNo OBJECT-TYPE
			SYNTAX SerialNo
			MAX-ACCESS read-only
			STATUS current
			DESCRIPTION
				"Serial number"
		::= { gps3002c03v1Entry 39 }

		-- 1.3.6.1.4.1.10106.3.290901
		tsm3001c01v1 OBJECT IDENTIFIER ::= { albalaProducts 290901 }

		-- 1.3.6.1.4.1.10106.3.290901.1
		tsm3001c01v1Table  OBJECT-TYPE
			SYNTAX SEQUENCE OF Tsm3001c01v1Entry
			MAX-ACCESS not-accessible
			STATUS current
			DESCRIPTION
				"Module  TSM3001C01V1 Table"
			::= { tsm3001c01v1 1 }

		-- 1.3.6.1.4.1.10106.3.290901.1.1
		tsm3001c01v1Entry  OBJECT-TYPE
			SYNTAX Tsm3001c01v1Entry
			MAX-ACCESS not-accessible
			STATUS current
			DESCRIPTION
				"Module TSM3001C01V1 Entry"
			INDEX { tsm3001c01v1Index }
			::= { tsm3001c01v1Table 1 }

			Tsm3001c01v1Entry ::=
			SEQUENCE {
				tsm3001c01v1Index
				ModuleIndex,
				tsm3001c01v1NoTsNat
				BitFail,
				tsm3001c01v1NoTsNatTrapEnable
				AlarmEnable,
				tsm3001c01v1NoReplac
				BitFail,
				tsm3001c01v1NoReplacTrapEnable
				AlarmEnable,
				tsm3001c01v1BadTsidNat
				BitFail,
				tsm3001c01v1BadTsidNatTrapEnable
				AlarmEnable,
				tsm3001c01v1FragPatNat
				BitFail,
				tsm3001c01v1FragNitNat
				BitFail,
				tsm3001c01v1FragSdtNat
				BitFail,
				tsm3001c01v1FragEitNat
				BitFail,
				tsm3001c01v1NoTsReg
				BitFail,
				tsm3001c01v1NoTsRegTrapEnable
				AlarmEnable,
				tsm3001c01v1BadTsidReg
				BitFail,
				tsm3001c01v1BadTsidRegTrapEnable
				AlarmEnable,
				tsm3001c01v1FragPatReg
				BitFail,
				tsm3001c01v1FragNitReg
				BitFail,
				tsm3001c01v1SerialNo
				SerialNo
			 }

		-- 1.3.6.1.4.1.10106.3.101291.1.1.1
		tsm3001c01v1Index OBJECT-TYPE
			SYNTAX ModuleIndex
			MAX-ACCESS read-only
			STATUS current
			DESCRIPTION
				"Index of TSM3001C01V1 Table"
		::= { tsm3001c01v1Entry 1 }

		-- 1.3.6.1.4.1.10106.3.101291.1.1.3
		tsm3001c01v1NoTsNat OBJECT-TYPE
			SYNTAX BitFail
			MAX-ACCESS read-only
			STATUS current
			DESCRIPTION
				"Indicates no national TS signal"
		::= { tsm3001c01v1Entry 3 }

		-- 1.3.6.1.4.1.10106.3.101291.1.1.4
		tsm3001c01v1NoTsNatTrapEnable OBJECT-TYPE
			SYNTAX AlarmEnable
			MAX-ACCESS read-write
			STATUS current
			DESCRIPTION
				"Indicates no national TS signal Trap Enable"
		::= { tsm3001c01v1Entry 4 }

		-- 1.3.6.1.4.1.10106.3.101291.1.1.5
		tsm3001c01v1NoReplac OBJECT-TYPE
			SYNTAX BitFail
			MAX-ACCESS read-only
			STATUS current
			DESCRIPTION
				"Indicates that no replacement is performed"
		::= { tsm3001c01v1Entry 5 }

		-- 1.3.6.1.4.1.10106.3.101291.1.1.6
		tsm3001c01v1NoReplacTrapEnable OBJECT-TYPE
			SYNTAX AlarmEnable
			MAX-ACCESS read-write
			STATUS current
			DESCRIPTION
				"Indicates that no replacement is performed Trap Enable"
		::= { tsm3001c01v1Entry 6 }

		-- 1.3.6.1.4.1.10106.3.101291.1.1.7
		tsm3001c01v1BadTsidNat OBJECT-TYPE
			SYNTAX BitFail
			MAX-ACCESS read-only
			STATUS current
			DESCRIPTION
				"Indicates that the national TS ID is not correct"
		::= { tsm3001c01v1Entry 7 }

		-- 1.3.6.1.4.1.10106.3.101291.1.1.8
		tsm3001c01v1BadTsidNatTrapEnable OBJECT-TYPE
			SYNTAX AlarmEnable
			MAX-ACCESS read-write
			STATUS current
			DESCRIPTION
				"Indicates that the national TS ID is not correct Trap Enable"
		::= { tsm3001c01v1Entry 8 }

		-- 1.3.6.1.4.1.10106.3.101291.1.1.9
		tsm3001c01v1FragPatNat OBJECT-TYPE
			SYNTAX BitFail
			MAX-ACCESS read-only
			STATUS current
			DESCRIPTION
				"Indicates that the PAT is fragmented in the national TS signal"
		::= { tsm3001c01v1Entry 9 }

		-- 1.3.6.1.4.1.10106.3.101291.1.1.11
		tsm3001c01v1FragNitNat OBJECT-TYPE
			SYNTAX BitFail
			MAX-ACCESS read-only
			STATUS current
			DESCRIPTION
				"Indicates that the NIT is fragmented in the national TS signal"
		::= { tsm3001c01v1Entry 11 }

		-- 1.3.6.1.4.1.10106.3.101291.1.1.13
		tsm3001c01v1FragSdtNat OBJECT-TYPE
			SYNTAX BitFail
			MAX-ACCESS read-only
			STATUS current
			DESCRIPTION
				"Indicates that the SDT is fragmented in the national TS signal"
		::= { tsm3001c01v1Entry 13 }

		-- 1.3.6.1.4.1.10106.3.101291.1.1.15
		tsm3001c01v1FragEitNat OBJECT-TYPE
			SYNTAX BitFail
			MAX-ACCESS read-only
			STATUS current
			DESCRIPTION
				"Indicates that the EIT is fragmented in the national TS signal"
		::= { tsm3001c01v1Entry 15 }

		-- 1.3.6.1.4.1.10106.3.101291.1.1.17
		tsm3001c01v1NoTsReg OBJECT-TYPE
			SYNTAX BitFail
			MAX-ACCESS read-only
			STATUS current
			DESCRIPTION
				"Indicates no regional TS signal"
		::= { tsm3001c01v1Entry 17 }

		-- 1.3.6.1.4.1.10106.3.101291.1.1.18
		tsm3001c01v1NoTsRegTrapEnable OBJECT-TYPE
			SYNTAX AlarmEnable
			MAX-ACCESS read-write
			STATUS current
			DESCRIPTION
				"Indicates no regional TS signal Trap Enable"
		::= { tsm3001c01v1Entry 18 }

		-- 1.3.6.1.4.1.10106.3.101291.1.1.19
		tsm3001c01v1BadTsidReg OBJECT-TYPE
			SYNTAX BitFail
			MAX-ACCESS read-only
			STATUS current
			DESCRIPTION
				"Indicates that the regional TS ID is not correct"
		::= { tsm3001c01v1Entry 19 }

		-- 1.3.6.1.4.1.10106.3.101291.1.1.20
		tsm3001c01v1BadTsidRegTrapEnable OBJECT-TYPE
			SYNTAX AlarmEnable
			MAX-ACCESS read-write
			STATUS current
			DESCRIPTION
				"Indicates that the regional TS ID is not correct Trap Enable"
		::= { tsm3001c01v1Entry 20 }

		-- 1.3.6.1.4.1.10106.3.101291.1.1.21
		tsm3001c01v1FragPatReg OBJECT-TYPE
			SYNTAX BitFail
			MAX-ACCESS read-only
			STATUS current
			DESCRIPTION
				"Indicates that the PAT is fragmented in the regional TS signal"
		::= { tsm3001c01v1Entry 21 }

		-- 1.3.6.1.4.1.10106.3.101291.1.1.23
		tsm3001c01v1FragNitReg OBJECT-TYPE
			SYNTAX BitFail
			MAX-ACCESS read-only
			STATUS current
			DESCRIPTION
				"Indicates that the NIT is fragmented in the regional TS signal"
		::= { tsm3001c01v1Entry 23 }

		-- 1.3.6.1.4.1.10106.3.101291.1.1.25
		tsm3001c01v1SerialNo OBJECT-TYPE
			SYNTAX SerialNo
			MAX-ACCESS read-only
			STATUS current
			DESCRIPTION
				"Serial number"
		::= { tsm3001c01v1Entry 25 }

		-- 1.3.6.1.4.1.10106.3.295301
		tpg3001c01v1 OBJECT IDENTIFIER ::= { albalaProducts 295301 }

		-- 1.3.6.1.4.1.10106.3.295301.1
		tpg3001c01v1Table  OBJECT-TYPE
			SYNTAX SEQUENCE OF Tpg3001c01v1Entry
			MAX-ACCESS not-accessible
			STATUS current
			DESCRIPTION
				"Module  TPG3001C01V1 Table"
			::= { tpg3001c01v1 1 }

		-- 1.3.6.1.4.1.10106.3.295301.1.1
		tpg3001c01v1Entry  OBJECT-TYPE
			SYNTAX Tpg3001c01v1Entry
			MAX-ACCESS not-accessible
			STATUS current
			DESCRIPTION
				"Module TPG3001C01V1 Entry"
			INDEX { tpg3001c01v1Index }
			::= { tpg3001c01v1Table 1 }

			Tpg3001c01v1Entry ::=
			SEQUENCE {
				tpg3001c01v1Index
				ModuleIndex,
				tpg3001c01v1Lines
				Bit06251525,
				tpg3001c01v1Genlock
				Bit0Ena1Dis,
				tpg3001c01v1EmbedBits
				Bit024120,
				tpg3001c01v1TestSignalA
				Uint6,
				tpg3001c01v1ColourA
				Bit0Ena1Dis,
				tpg3001c01v1VitcInsA
				Bit0Dis1Ena,
				tpg3001c01v1VitcModeA
				Bit0Ndr1Drp,
				tpg3001c01v1VitcInsLineA
				VbiLine,
				tpg3001c01v1SchA
				Sch2,
				tpg3001c01v1EmbedA
				Bit0No1Yes,
				tpg3001c01v1MuteAudA
				Bit0No1Yes,
				tpg3001c01v1GroupA
				EmbedGroup,
				tpg3001c01v1AudCh1A
				AudioFreq2,
				tpg3001c01v1AudCh2A
				AudioFreq2,
				tpg3001c01v1AudCh3A
				AudioFreq2,
				tpg3001c01v1AudCh4A
				AudioFreq2,
				tpg3001c01v1TextForeColA
				CaptColour2,
				tpg3001c01v1TextBackColA
				CaptColour2,
				tpg3001c01v1TextInsModeA
				CaptMode1,
				tpg3001c01v1TextSetA
				CaptSet1,
				tpg3001c01v1WhiteLineA
				Bit0Dis1Ena,
				tpg3001c01v1FrameDelayA
				DelayFram1,
				tpg3001c01v1VDelayA
				DelayLines1,
				tpg3001c01v1HDelayA
				DelayPixel1,
				tpg3001c01v1HDelayFineA
				DelayX144Ps,
				tpg3001c01v1TestSignalB
				Uint6,
				tpg3001c01v1ColourB
				Bit0Ena1Dis,
				tpg3001c01v1VitcInsB
				Bit0Dis1Ena,
				tpg3001c01v1VitcModeB
				Bit0Ndr1Drp,
				tpg3001c01v1VitcInsLineB
				VbiLine,
				tpg3001c01v1SchB
				Sch2,
				tpg3001c01v1EmbedB
				Bit0No1Yes,
				tpg3001c01v1MuteAudB
				Bit0No1Yes,
				tpg3001c01v1GroupB
				EmbedGroup,
				tpg3001c01v1AudCh1B
				AudioFreq2,
				tpg3001c01v1AudCh2B
				AudioFreq2,
				tpg3001c01v1AudCh3B
				AudioFreq2,
				tpg3001c01v1AudCh4B
				AudioFreq2,
				tpg3001c01v1TextForeColB
				CaptColour2,
				tpg3001c01v1TextBackColB
				CaptColour2,
				tpg3001c01v1TextInsModeB
				CaptMode1,
				tpg3001c01v1TextSetB
				CaptSet1,
				tpg3001c01v1WhiteLineB
				Bit0Dis1Ena,
				tpg3001c01v1FrameDelayB
				DelayFram1,
				tpg3001c01v1VDelayB
				DelayLines1,
				tpg3001c01v1HDelayB
				DelayPixel1,
				tpg3001c01v1HDelayFineB
				DelayX144Ps,
				tpg3001c01v1OsdSet1L8Ch1
				CaptChar1,
				tpg3001c01v1OsdSet1L8Ch2
				CaptChar1,
				tpg3001c01v1OsdSet1L8Ch3
				CaptChar1,
				tpg3001c01v1OsdSet1L8Ch4
				CaptChar1,
				tpg3001c01v1OsdSet1L8Ch5
				CaptChar1,
				tpg3001c01v1OsdSet1L8Ch6
				CaptChar1,
				tpg3001c01v1OsdSet1L8Ch7
				CaptChar1,
				tpg3001c01v1OsdSet1L8Ch8
				CaptChar1,
				tpg3001c01v1OsdSet1L8Ch9
				CaptChar1,
				tpg3001c01v1OsdSet1L8Ch10
				CaptChar1,
				tpg3001c01v1OsdSet1L8Ch11
				CaptChar1,
				tpg3001c01v1OsdSet1L8Ch12
				CaptChar1,
				tpg3001c01v1OsdSet1L8Ch13
				CaptChar1,
				tpg3001c01v1OsdSet1L8Ch14
				CaptChar1,
				tpg3001c01v1OsdSet1L8Ch15
				CaptChar1,
				tpg3001c01v1OsdSet1L8Ch16
				CaptChar1,
				tpg3001c01v1OsdSet2L8Ch1
				CaptChar1,
				tpg3001c01v1OsdSet2L8Ch2
				CaptChar1,
				tpg3001c01v1OsdSet2L8Ch3
				CaptChar1,
				tpg3001c01v1OsdSet2L8Ch4
				CaptChar1,
				tpg3001c01v1OsdSet2L8Ch5
				CaptChar1,
				tpg3001c01v1OsdSet2L8Ch6
				CaptChar1,
				tpg3001c01v1OsdSet2L8Ch7
				CaptChar1,
				tpg3001c01v1OsdSet2L8Ch8
				CaptChar1,
				tpg3001c01v1OsdSet2L8Ch9
				CaptChar1,
				tpg3001c01v1OsdSet2L8Ch10
				CaptChar1,
				tpg3001c01v1OsdSet2L8Ch11
				CaptChar1,
				tpg3001c01v1OsdSet2L8Ch12
				CaptChar1,
				tpg3001c01v1OsdSet2L8Ch13
				CaptChar1,
				tpg3001c01v1OsdSet2L8Ch14
				CaptChar1,
				tpg3001c01v1OsdSet2L8Ch15
				CaptChar1,
				tpg3001c01v1OsdSet2L8Ch16
				CaptChar1,
				tpg3001c01v1VitcHourOff
				TimeH1,
				tpg3001c01v1VitcMinOff
				TimeM1,
				tpg3001c01v1VitcSecOff
				TimeS1,
				tpg3001c01v1RefPresence
				Bit0No1Yes,
				tpg3001c01v1RefLock
				Bit0No1Yes,
				tpg3001c01v1VitcHour
				TimeH1,
				tpg3001c01v1VitcMin
				TimeM1,
				tpg3001c01v1VitcSec
				TimeS1,
				tpg3001c01v1SerialNo
				SerialNo
			 }

		-- 1.3.6.1.4.1.10106.3.101291.1.1.1
		tpg3001c01v1Index OBJECT-TYPE
			SYNTAX ModuleIndex
			MAX-ACCESS read-only
			STATUS current
			DESCRIPTION
				"Index of TPG3001C01V1 Table"
		::= { tpg3001c01v1Entry 1 }

		-- 1.3.6.1.4.1.10106.3.101291.1.1.3
		tpg3001c01v1Lines OBJECT-TYPE
			SYNTAX Bit06251525
			MAX-ACCESS read-write
			STATUS current
			DESCRIPTION
				"TV output signal format"
		::= { tpg3001c01v1Entry 3 }

		-- 1.3.6.1.4.1.10106.3.101291.1.1.5
		tpg3001c01v1Genlock OBJECT-TYPE
			SYNTAX Bit0Ena1Dis
			MAX-ACCESS read-write
			STATUS current
			DESCRIPTION
				"Allows genlocking to internal chassis clock reference"
		::= { tpg3001c01v1Entry 5 }

		-- 1.3.6.1.4.1.10106.3.101291.1.1.7
		tpg3001c01v1EmbedBits OBJECT-TYPE
			SYNTAX Bit024120
			MAX-ACCESS read-write
			STATUS current
			DESCRIPTION
				"Allows selecting the number of bits of the embedded audio"
		::= { tpg3001c01v1Entry 7 }

		-- 1.3.6.1.4.1.10106.3.101291.1.1.9
		tpg3001c01v1TestSignalA OBJECT-TYPE
			SYNTAX Uint6
			MAX-ACCESS read-write
			STATUS current
			DESCRIPTION
				"Allows selecting the generated video signal pattern"
		::= { tpg3001c01v1Entry 9 }

		-- 1.3.6.1.4.1.10106.3.101291.1.1.11
		tpg3001c01v1ColourA OBJECT-TYPE
			SYNTAX Bit0Ena1Dis
			MAX-ACCESS read-write
			STATUS current
			DESCRIPTION
				"Allows disabling colour"
		::= { tpg3001c01v1Entry 11 }

		-- 1.3.6.1.4.1.10106.3.101291.1.1.13
		tpg3001c01v1VitcInsA OBJECT-TYPE
			SYNTAX Bit0Dis1Ena
			MAX-ACCESS read-write
			STATUS current
			DESCRIPTION
				"Allows enabling VITC insetion"
		::= { tpg3001c01v1Entry 13 }

		-- 1.3.6.1.4.1.10106.3.101291.1.1.15
		tpg3001c01v1VitcModeA OBJECT-TYPE
			SYNTAX Bit0Ndr1Drp
			MAX-ACCESS read-write
			STATUS current
			DESCRIPTION
				"Allows selecting the VITC mode"
		::= { tpg3001c01v1Entry 15 }

		-- 1.3.6.1.4.1.10106.3.101291.1.1.17
		tpg3001c01v1VitcInsLineA OBJECT-TYPE
			SYNTAX VbiLine
			MAX-ACCESS read-write
			STATUS current
			DESCRIPTION
				"Allows adjusting the VITC insertion line"
		::= { tpg3001c01v1Entry 17 }

		-- 1.3.6.1.4.1.10106.3.101291.1.1.19
		tpg3001c01v1SchA OBJECT-TYPE
			SYNTAX Sch2
			MAX-ACCESS read-write
			STATUS current
			DESCRIPTION
				"Allows adjustint the CCVS output SCH"
		::= { tpg3001c01v1Entry 19 }

		-- 1.3.6.1.4.1.10106.3.101291.1.1.21
		tpg3001c01v1EmbedA OBJECT-TYPE
			SYNTAX Bit0No1Yes
			MAX-ACCESS read-write
			STATUS current
			DESCRIPTION
				"Allows selecting if the audio is embedded"
		::= { tpg3001c01v1Entry 21 }

		-- 1.3.6.1.4.1.10106.3.101291.1.1.23
		tpg3001c01v1MuteAudA OBJECT-TYPE
			SYNTAX Bit0No1Yes
			MAX-ACCESS read-write
			STATUS current
			DESCRIPTION
				"Allows muting audio"
		::= { tpg3001c01v1Entry 23 }

		-- 1.3.6.1.4.1.10106.3.101291.1.1.25
		tpg3001c01v1GroupA OBJECT-TYPE
			SYNTAX EmbedGroup
			MAX-ACCESS read-write
			STATUS current
			DESCRIPTION
				"Allows selecting the group in which the audio is embedded"
		::= { tpg3001c01v1Entry 25 }

		-- 1.3.6.1.4.1.10106.3.101291.1.1.27
		tpg3001c01v1AudCh1A OBJECT-TYPE
			SYNTAX AudioFreq2
			MAX-ACCESS read-write
			STATUS current
			DESCRIPTION
				"Allows selecting the audio signal in channel 1"
		::= { tpg3001c01v1Entry 27 }

		-- 1.3.6.1.4.1.10106.3.101291.1.1.29
		tpg3001c01v1AudCh2A OBJECT-TYPE
			SYNTAX AudioFreq2
			MAX-ACCESS read-write
			STATUS current
			DESCRIPTION
				"Allows selecting the audio signal in channel 2"
		::= { tpg3001c01v1Entry 29 }

		-- 1.3.6.1.4.1.10106.3.101291.1.1.31
		tpg3001c01v1AudCh3A OBJECT-TYPE
			SYNTAX AudioFreq2
			MAX-ACCESS read-write
			STATUS current
			DESCRIPTION
				"Allows selecting the audio signal in channel 3"
		::= { tpg3001c01v1Entry 31 }

		-- 1.3.6.1.4.1.10106.3.101291.1.1.33
		tpg3001c01v1AudCh4A OBJECT-TYPE
			SYNTAX AudioFreq2
			MAX-ACCESS read-write
			STATUS current
			DESCRIPTION
				"Allows selecting the audio signal in channel 4"
		::= { tpg3001c01v1Entry 33 }

		-- 1.3.6.1.4.1.10106.3.101291.1.1.35
		tpg3001c01v1TextForeColA OBJECT-TYPE
			SYNTAX CaptColour2
			MAX-ACCESS read-write
			STATUS current
			DESCRIPTION
				"Allows selecting caption foreground colour"
		::= { tpg3001c01v1Entry 35 }

		-- 1.3.6.1.4.1.10106.3.101291.1.1.37
		tpg3001c01v1TextBackColA OBJECT-TYPE
			SYNTAX CaptColour2
			MAX-ACCESS read-write
			STATUS current
			DESCRIPTION
				"Allows selecting caption background colour"
		::= { tpg3001c01v1Entry 37 }

		-- 1.3.6.1.4.1.10106.3.101291.1.1.39
		tpg3001c01v1TextInsModeA OBJECT-TYPE
			SYNTAX CaptMode1
			MAX-ACCESS read-write
			STATUS current
			DESCRIPTION
				"Allows selectign the caption insertion mode"
		::= { tpg3001c01v1Entry 39 }

		-- 1.3.6.1.4.1.10106.3.101291.1.1.41
		tpg3001c01v1TextSetA OBJECT-TYPE
			SYNTAX CaptSet1
			MAX-ACCESS read-write
			STATUS current
			DESCRIPTION
				"Allows selecting a caption from a set"
		::= { tpg3001c01v1Entry 41 }

		-- 1.3.6.1.4.1.10106.3.101291.1.1.43
		tpg3001c01v1WhiteLineA OBJECT-TYPE
			SYNTAX Bit0Dis1Ena
			MAX-ACCESS read-write
			STATUS current
			DESCRIPTION
				"Allows inserting a white line for field 1 identification in 626 lines"
		::= { tpg3001c01v1Entry 43 }

		-- 1.3.6.1.4.1.10106.3.101291.1.1.45
		tpg3001c01v1FrameDelayA OBJECT-TYPE
			SYNTAX DelayFram1
			MAX-ACCESS read-write
			STATUS current
			DESCRIPTION
				"Allows adjusting the video frame delay"
		::= { tpg3001c01v1Entry 45 }

		-- 1.3.6.1.4.1.10106.3.101291.1.1.47
		tpg3001c01v1VDelayA OBJECT-TYPE
			SYNTAX DelayLines1
			MAX-ACCESS read-write
			STATUS current
			DESCRIPTION
				"Allows adjusting the video vertical delay"
		::= { tpg3001c01v1Entry 47 }

		-- 1.3.6.1.4.1.10106.3.101291.1.1.49
		tpg3001c01v1HDelayA OBJECT-TYPE
			SYNTAX DelayPixel1
			MAX-ACCESS read-write
			STATUS current
			DESCRIPTION
				"Allows adjusting the video horizontal delay"
		::= { tpg3001c01v1Entry 49 }

		-- 1.3.6.1.4.1.10106.3.101291.1.1.51
		tpg3001c01v1HDelayFineA OBJECT-TYPE
			SYNTAX DelayX144Ps
			MAX-ACCESS read-write
			STATUS current
			DESCRIPTION
				"Allows adjusting the video horizontal delay (fine)"
		::= { tpg3001c01v1Entry 51 }

		-- 1.3.6.1.4.1.10106.3.101291.1.1.53
		tpg3001c01v1TestSignalB OBJECT-TYPE
			SYNTAX Uint6
			MAX-ACCESS read-write
			STATUS current
			DESCRIPTION
				"Allows selecting the generated video signal pattern"
		::= { tpg3001c01v1Entry 53 }

		-- 1.3.6.1.4.1.10106.3.101291.1.1.55
		tpg3001c01v1ColourB OBJECT-TYPE
			SYNTAX Bit0Ena1Dis
			MAX-ACCESS read-write
			STATUS current
			DESCRIPTION
				"Allows disabling colour"
		::= { tpg3001c01v1Entry 55 }

		-- 1.3.6.1.4.1.10106.3.101291.1.1.57
		tpg3001c01v1VitcInsB OBJECT-TYPE
			SYNTAX Bit0Dis1Ena
			MAX-ACCESS read-write
			STATUS current
			DESCRIPTION
				"Allows enabling VITC insetion"
		::= { tpg3001c01v1Entry 57 }

		-- 1.3.6.1.4.1.10106.3.101291.1.1.59
		tpg3001c01v1VitcModeB OBJECT-TYPE
			SYNTAX Bit0Ndr1Drp
			MAX-ACCESS read-write
			STATUS current
			DESCRIPTION
				"Allows selecting the VITC mode"
		::= { tpg3001c01v1Entry 59 }

		-- 1.3.6.1.4.1.10106.3.101291.1.1.61
		tpg3001c01v1VitcInsLineB OBJECT-TYPE
			SYNTAX VbiLine
			MAX-ACCESS read-write
			STATUS current
			DESCRIPTION
				"Allows adjusting the VITC insertion line"
		::= { tpg3001c01v1Entry 61 }

		-- 1.3.6.1.4.1.10106.3.101291.1.1.63
		tpg3001c01v1SchB OBJECT-TYPE
			SYNTAX Sch2
			MAX-ACCESS read-write
			STATUS current
			DESCRIPTION
				"Allows adjustint the CCVS output SCH"
		::= { tpg3001c01v1Entry 63 }

		-- 1.3.6.1.4.1.10106.3.101291.1.1.65
		tpg3001c01v1EmbedB OBJECT-TYPE
			SYNTAX Bit0No1Yes
			MAX-ACCESS read-write
			STATUS current
			DESCRIPTION
				"Allows selecting if the audio is embedded"
		::= { tpg3001c01v1Entry 65 }

		-- 1.3.6.1.4.1.10106.3.101291.1.1.67
		tpg3001c01v1MuteAudB OBJECT-TYPE
			SYNTAX Bit0No1Yes
			MAX-ACCESS read-write
			STATUS current
			DESCRIPTION
				"Allows muting audio"
		::= { tpg3001c01v1Entry 67 }

		-- 1.3.6.1.4.1.10106.3.101291.1.1.69
		tpg3001c01v1GroupB OBJECT-TYPE
			SYNTAX EmbedGroup
			MAX-ACCESS read-write
			STATUS current
			DESCRIPTION
				"Allows selecting the group in which the audio is embedded"
		::= { tpg3001c01v1Entry 69 }

		-- 1.3.6.1.4.1.10106.3.101291.1.1.71
		tpg3001c01v1AudCh1B OBJECT-TYPE
			SYNTAX AudioFreq2
			MAX-ACCESS read-write
			STATUS current
			DESCRIPTION
				"Allows selecting the audio signal in channel 1"
		::= { tpg3001c01v1Entry 71 }

		-- 1.3.6.1.4.1.10106.3.101291.1.1.73
		tpg3001c01v1AudCh2B OBJECT-TYPE
			SYNTAX AudioFreq2
			MAX-ACCESS read-write
			STATUS current
			DESCRIPTION
				"Allows selecting the audio signal in channel 2"
		::= { tpg3001c01v1Entry 73 }

		-- 1.3.6.1.4.1.10106.3.101291.1.1.75
		tpg3001c01v1AudCh3B OBJECT-TYPE
			SYNTAX AudioFreq2
			MAX-ACCESS read-write
			STATUS current
			DESCRIPTION
				"Allows selecting the audio signal in channel 3"
		::= { tpg3001c01v1Entry 75 }

		-- 1.3.6.1.4.1.10106.3.101291.1.1.77
		tpg3001c01v1AudCh4B OBJECT-TYPE
			SYNTAX AudioFreq2
			MAX-ACCESS read-write
			STATUS current
			DESCRIPTION
				"Allows selecting the audio signal in channel 4"
		::= { tpg3001c01v1Entry 77 }

		-- 1.3.6.1.4.1.10106.3.101291.1.1.79
		tpg3001c01v1TextForeColB OBJECT-TYPE
			SYNTAX CaptColour2
			MAX-ACCESS read-write
			STATUS current
			DESCRIPTION
				"Allows selecting caption foreground colour"
		::= { tpg3001c01v1Entry 79 }

		-- 1.3.6.1.4.1.10106.3.101291.1.1.81
		tpg3001c01v1TextBackColB OBJECT-TYPE
			SYNTAX CaptColour2
			MAX-ACCESS read-write
			STATUS current
			DESCRIPTION
				"Allows selecting caption background colour"
		::= { tpg3001c01v1Entry 81 }

		-- 1.3.6.1.4.1.10106.3.101291.1.1.83
		tpg3001c01v1TextInsModeB OBJECT-TYPE
			SYNTAX CaptMode1
			MAX-ACCESS read-write
			STATUS current
			DESCRIPTION
				"Allows selectign the caption insertion mode"
		::= { tpg3001c01v1Entry 83 }

		-- 1.3.6.1.4.1.10106.3.101291.1.1.85
		tpg3001c01v1TextSetB OBJECT-TYPE
			SYNTAX CaptSet1
			MAX-ACCESS read-write
			STATUS current
			DESCRIPTION
				"Allows selecting a caption from a set"
		::= { tpg3001c01v1Entry 85 }

		-- 1.3.6.1.4.1.10106.3.101291.1.1.87
		tpg3001c01v1WhiteLineB OBJECT-TYPE
			SYNTAX Bit0Dis1Ena
			MAX-ACCESS read-write
			STATUS current
			DESCRIPTION
				"Allows inserting a white line for field 1 identification in 626 lines"
		::= { tpg3001c01v1Entry 87 }

		-- 1.3.6.1.4.1.10106.3.101291.1.1.89
		tpg3001c01v1FrameDelayB OBJECT-TYPE
			SYNTAX DelayFram1
			MAX-ACCESS read-write
			STATUS current
			DESCRIPTION
				"Allows adjusting the video frame delay"
		::= { tpg3001c01v1Entry 89 }

		-- 1.3.6.1.4.1.10106.3.101291.1.1.91
		tpg3001c01v1VDelayB OBJECT-TYPE
			SYNTAX DelayLines1
			MAX-ACCESS read-write
			STATUS current
			DESCRIPTION
				"Allows adjusting the video vertical delay"
		::= { tpg3001c01v1Entry 91 }

		-- 1.3.6.1.4.1.10106.3.101291.1.1.93
		tpg3001c01v1HDelayB OBJECT-TYPE
			SYNTAX DelayPixel1
			MAX-ACCESS read-write
			STATUS current
			DESCRIPTION
				"Allows adjusting the video horizontal delay"
		::= { tpg3001c01v1Entry 93 }

		-- 1.3.6.1.4.1.10106.3.101291.1.1.95
		tpg3001c01v1HDelayFineB OBJECT-TYPE
			SYNTAX DelayX144Ps
			MAX-ACCESS read-write
			STATUS current
			DESCRIPTION
				"Allows adjusting the video horizontal delay (fine)"
		::= { tpg3001c01v1Entry 95 }

		-- 1.3.6.1.4.1.10106.3.101291.1.1.97
		tpg3001c01v1OsdSet1L8Ch1 OBJECT-TYPE
			SYNTAX CaptChar1
			MAX-ACCESS read-write
			STATUS current
			DESCRIPTION
				"Text line 8 column 1"
		::= { tpg3001c01v1Entry 97 }

		-- 1.3.6.1.4.1.10106.3.101291.1.1.99
		tpg3001c01v1OsdSet1L8Ch2 OBJECT-TYPE
			SYNTAX CaptChar1
			MAX-ACCESS read-write
			STATUS current
			DESCRIPTION
				"Text line 8 column 2"
		::= { tpg3001c01v1Entry 99 }

		-- 1.3.6.1.4.1.10106.3.101291.1.1.101
		tpg3001c01v1OsdSet1L8Ch3 OBJECT-TYPE
			SYNTAX CaptChar1
			MAX-ACCESS read-write
			STATUS current
			DESCRIPTION
				"Text line 8 column 3"
		::= { tpg3001c01v1Entry 101 }

		-- 1.3.6.1.4.1.10106.3.101291.1.1.103
		tpg3001c01v1OsdSet1L8Ch4 OBJECT-TYPE
			SYNTAX CaptChar1
			MAX-ACCESS read-write
			STATUS current
			DESCRIPTION
				"Text line 8 column 4"
		::= { tpg3001c01v1Entry 103 }

		-- 1.3.6.1.4.1.10106.3.101291.1.1.105
		tpg3001c01v1OsdSet1L8Ch5 OBJECT-TYPE
			SYNTAX CaptChar1
			MAX-ACCESS read-write
			STATUS current
			DESCRIPTION
				"Text line 8 column 5"
		::= { tpg3001c01v1Entry 105 }

		-- 1.3.6.1.4.1.10106.3.101291.1.1.107
		tpg3001c01v1OsdSet1L8Ch6 OBJECT-TYPE
			SYNTAX CaptChar1
			MAX-ACCESS read-write
			STATUS current
			DESCRIPTION
				"Text line 8 column 6"
		::= { tpg3001c01v1Entry 107 }

		-- 1.3.6.1.4.1.10106.3.101291.1.1.109
		tpg3001c01v1OsdSet1L8Ch7 OBJECT-TYPE
			SYNTAX CaptChar1
			MAX-ACCESS read-write
			STATUS current
			DESCRIPTION
				"Text line 8 column 7"
		::= { tpg3001c01v1Entry 109 }

		-- 1.3.6.1.4.1.10106.3.101291.1.1.111
		tpg3001c01v1OsdSet1L8Ch8 OBJECT-TYPE
			SYNTAX CaptChar1
			MAX-ACCESS read-write
			STATUS current
			DESCRIPTION
				"Text line 8 column 8"
		::= { tpg3001c01v1Entry 111 }

		-- 1.3.6.1.4.1.10106.3.101291.1.1.113
		tpg3001c01v1OsdSet1L8Ch9 OBJECT-TYPE
			SYNTAX CaptChar1
			MAX-ACCESS read-write
			STATUS current
			DESCRIPTION
				"Text line 8 column 9"
		::= { tpg3001c01v1Entry 113 }

		-- 1.3.6.1.4.1.10106.3.101291.1.1.115
		tpg3001c01v1OsdSet1L8Ch10 OBJECT-TYPE
			SYNTAX CaptChar1
			MAX-ACCESS read-write
			STATUS current
			DESCRIPTION
				"Text line 8 column 10"
		::= { tpg3001c01v1Entry 115 }

		-- 1.3.6.1.4.1.10106.3.101291.1.1.117
		tpg3001c01v1OsdSet1L8Ch11 OBJECT-TYPE
			SYNTAX CaptChar1
			MAX-ACCESS read-write
			STATUS current
			DESCRIPTION
				"Text line 8 column 11"
		::= { tpg3001c01v1Entry 117 }

		-- 1.3.6.1.4.1.10106.3.101291.1.1.119
		tpg3001c01v1OsdSet1L8Ch12 OBJECT-TYPE
			SYNTAX CaptChar1
			MAX-ACCESS read-write
			STATUS current
			DESCRIPTION
				"Text line 8 column 12"
		::= { tpg3001c01v1Entry 119 }

		-- 1.3.6.1.4.1.10106.3.101291.1.1.121
		tpg3001c01v1OsdSet1L8Ch13 OBJECT-TYPE
			SYNTAX CaptChar1
			MAX-ACCESS read-write
			STATUS current
			DESCRIPTION
				"Text line 8 column 13"
		::= { tpg3001c01v1Entry 121 }

		-- 1.3.6.1.4.1.10106.3.101291.1.1.123
		tpg3001c01v1OsdSet1L8Ch14 OBJECT-TYPE
			SYNTAX CaptChar1
			MAX-ACCESS read-write
			STATUS current
			DESCRIPTION
				"Text line 8 column 14"
		::= { tpg3001c01v1Entry 123 }

		-- 1.3.6.1.4.1.10106.3.101291.1.1.125
		tpg3001c01v1OsdSet1L8Ch15 OBJECT-TYPE
			SYNTAX CaptChar1
			MAX-ACCESS read-write
			STATUS current
			DESCRIPTION
				"Text line 8 column 15"
		::= { tpg3001c01v1Entry 125 }

		-- 1.3.6.1.4.1.10106.3.101291.1.1.127
		tpg3001c01v1OsdSet1L8Ch16 OBJECT-TYPE
			SYNTAX CaptChar1
			MAX-ACCESS read-write
			STATUS current
			DESCRIPTION
				"Text line 8 column 16"
		::= { tpg3001c01v1Entry 127 }

		-- 1.3.6.1.4.1.10106.3.101291.1.1.129
		tpg3001c01v1OsdSet2L8Ch1 OBJECT-TYPE
			SYNTAX CaptChar1
			MAX-ACCESS read-write
			STATUS current
			DESCRIPTION
				"Text line 8 column 1"
		::= { tpg3001c01v1Entry 129 }

		-- 1.3.6.1.4.1.10106.3.101291.1.1.131
		tpg3001c01v1OsdSet2L8Ch2 OBJECT-TYPE
			SYNTAX CaptChar1
			MAX-ACCESS read-write
			STATUS current
			DESCRIPTION
				"Text line 8 column 2"
		::= { tpg3001c01v1Entry 131 }

		-- 1.3.6.1.4.1.10106.3.101291.1.1.133
		tpg3001c01v1OsdSet2L8Ch3 OBJECT-TYPE
			SYNTAX CaptChar1
			MAX-ACCESS read-write
			STATUS current
			DESCRIPTION
				"Text line 8 column 3"
		::= { tpg3001c01v1Entry 133 }

		-- 1.3.6.1.4.1.10106.3.101291.1.1.135
		tpg3001c01v1OsdSet2L8Ch4 OBJECT-TYPE
			SYNTAX CaptChar1
			MAX-ACCESS read-write
			STATUS current
			DESCRIPTION
				"Text line 8 column 4"
		::= { tpg3001c01v1Entry 135 }

		-- 1.3.6.1.4.1.10106.3.101291.1.1.137
		tpg3001c01v1OsdSet2L8Ch5 OBJECT-TYPE
			SYNTAX CaptChar1
			MAX-ACCESS read-write
			STATUS current
			DESCRIPTION
				"Text line 8 column 5"
		::= { tpg3001c01v1Entry 137 }

		-- 1.3.6.1.4.1.10106.3.101291.1.1.139
		tpg3001c01v1OsdSet2L8Ch6 OBJECT-TYPE
			SYNTAX CaptChar1
			MAX-ACCESS read-write
			STATUS current
			DESCRIPTION
				"Text line 8 column 6"
		::= { tpg3001c01v1Entry 139 }

		-- 1.3.6.1.4.1.10106.3.101291.1.1.141
		tpg3001c01v1OsdSet2L8Ch7 OBJECT-TYPE
			SYNTAX CaptChar1
			MAX-ACCESS read-write
			STATUS current
			DESCRIPTION
				"Text line 8 column 7"
		::= { tpg3001c01v1Entry 141 }

		-- 1.3.6.1.4.1.10106.3.101291.1.1.143
		tpg3001c01v1OsdSet2L8Ch8 OBJECT-TYPE
			SYNTAX CaptChar1
			MAX-ACCESS read-write
			STATUS current
			DESCRIPTION
				"Text line 8 column 8"
		::= { tpg3001c01v1Entry 143 }

		-- 1.3.6.1.4.1.10106.3.101291.1.1.145
		tpg3001c01v1OsdSet2L8Ch9 OBJECT-TYPE
			SYNTAX CaptChar1
			MAX-ACCESS read-write
			STATUS current
			DESCRIPTION
				"Text line 8 column 9"
		::= { tpg3001c01v1Entry 145 }

		-- 1.3.6.1.4.1.10106.3.101291.1.1.147
		tpg3001c01v1OsdSet2L8Ch10 OBJECT-TYPE
			SYNTAX CaptChar1
			MAX-ACCESS read-write
			STATUS current
			DESCRIPTION
				"Text line 8 column 10"
		::= { tpg3001c01v1Entry 147 }

		-- 1.3.6.1.4.1.10106.3.101291.1.1.149
		tpg3001c01v1OsdSet2L8Ch11 OBJECT-TYPE
			SYNTAX CaptChar1
			MAX-ACCESS read-write
			STATUS current
			DESCRIPTION
				"Text line 8 column 11"
		::= { tpg3001c01v1Entry 149 }

		-- 1.3.6.1.4.1.10106.3.101291.1.1.151
		tpg3001c01v1OsdSet2L8Ch12 OBJECT-TYPE
			SYNTAX CaptChar1
			MAX-ACCESS read-write
			STATUS current
			DESCRIPTION
				"Text line 8 column 12"
		::= { tpg3001c01v1Entry 151 }

		-- 1.3.6.1.4.1.10106.3.101291.1.1.153
		tpg3001c01v1OsdSet2L8Ch13 OBJECT-TYPE
			SYNTAX CaptChar1
			MAX-ACCESS read-write
			STATUS current
			DESCRIPTION
				"Text line 8 column 13"
		::= { tpg3001c01v1Entry 153 }

		-- 1.3.6.1.4.1.10106.3.101291.1.1.155
		tpg3001c01v1OsdSet2L8Ch14 OBJECT-TYPE
			SYNTAX CaptChar1
			MAX-ACCESS read-write
			STATUS current
			DESCRIPTION
				"Text line 8 column 14"
		::= { tpg3001c01v1Entry 155 }

		-- 1.3.6.1.4.1.10106.3.101291.1.1.157
		tpg3001c01v1OsdSet2L8Ch15 OBJECT-TYPE
			SYNTAX CaptChar1
			MAX-ACCESS read-write
			STATUS current
			DESCRIPTION
				"Text line 8 column 15"
		::= { tpg3001c01v1Entry 157 }

		-- 1.3.6.1.4.1.10106.3.101291.1.1.159
		tpg3001c01v1OsdSet2L8Ch16 OBJECT-TYPE
			SYNTAX CaptChar1
			MAX-ACCESS read-write
			STATUS current
			DESCRIPTION
				"Text line 8 column 16"
		::= { tpg3001c01v1Entry 159 }

		-- 1.3.6.1.4.1.10106.3.101291.1.1.161
		tpg3001c01v1VitcHourOff OBJECT-TYPE
			SYNTAX TimeH1
			MAX-ACCESS read-write
			STATUS current
			DESCRIPTION
				"Allows adjusting the VITC hours offset"
		::= { tpg3001c01v1Entry 161 }

		-- 1.3.6.1.4.1.10106.3.101291.1.1.163
		tpg3001c01v1VitcMinOff OBJECT-TYPE
			SYNTAX TimeM1
			MAX-ACCESS read-write
			STATUS current
			DESCRIPTION
				"Allows adjusting the VITC minutes offset"
		::= { tpg3001c01v1Entry 163 }

		-- 1.3.6.1.4.1.10106.3.101291.1.1.165
		tpg3001c01v1VitcSecOff OBJECT-TYPE
			SYNTAX TimeS1
			MAX-ACCESS read-write
			STATUS current
			DESCRIPTION
				"Allows adjusting the VITC seconds offset"
		::= { tpg3001c01v1Entry 165 }

		-- 1.3.6.1.4.1.10106.3.101291.1.1.167
		tpg3001c01v1RefPresence OBJECT-TYPE
			SYNTAX Bit0No1Yes
			MAX-ACCESS read-only
			STATUS current
			DESCRIPTION
				"Indicates that the chassis internal reference is present"
		::= { tpg3001c01v1Entry 167 }

		-- 1.3.6.1.4.1.10106.3.101291.1.1.169
		tpg3001c01v1RefLock OBJECT-TYPE
			SYNTAX Bit0No1Yes
			MAX-ACCESS read-only
			STATUS current
			DESCRIPTION
				"Indicates that the module's TCVCXO is locked to the chassis internal reference"
		::= { tpg3001c01v1Entry 169 }

		-- 1.3.6.1.4.1.10106.3.101291.1.1.171
		tpg3001c01v1VitcHour OBJECT-TYPE
			SYNTAX TimeH1
			MAX-ACCESS read-only
			STATUS current
			DESCRIPTION
				"Hour read from internal reference"
		::= { tpg3001c01v1Entry 171 }

		-- 1.3.6.1.4.1.10106.3.101291.1.1.173
		tpg3001c01v1VitcMin OBJECT-TYPE
			SYNTAX TimeM1
			MAX-ACCESS read-only
			STATUS current
			DESCRIPTION
				"Minute read from internal reference"
		::= { tpg3001c01v1Entry 173 }

		-- 1.3.6.1.4.1.10106.3.101291.1.1.175
		tpg3001c01v1VitcSec OBJECT-TYPE
			SYNTAX TimeS1
			MAX-ACCESS read-only
			STATUS current
			DESCRIPTION
				"Second read from internal reference"
		::= { tpg3001c01v1Entry 175 }

		-- 1.3.6.1.4.1.10106.3.101291.1.1.177
		tpg3001c01v1SerialNo OBJECT-TYPE
			SYNTAX SerialNo
			MAX-ACCESS read-only
			STATUS current
			DESCRIPTION
				"Serial number"
		::= { tpg3001c01v1Entry 177 }

		-- 1.3.6.1.4.1.10106.3.308701
		aac3008c01v1 OBJECT IDENTIFIER ::= { albalaProducts 308701 }

		-- 1.3.6.1.4.1.10106.3.308701.1
		aac3008c01v1Table  OBJECT-TYPE
			SYNTAX SEQUENCE OF Aac3008c01v1Entry
			MAX-ACCESS not-accessible
			STATUS current
			DESCRIPTION
				"Module  AAC3008C01V1 Table"
			::= { aac3008c01v1 1 }

		-- 1.3.6.1.4.1.10106.3.308701.1.1
		aac3008c01v1Entry  OBJECT-TYPE
			SYNTAX Aac3008c01v1Entry
			MAX-ACCESS not-accessible
			STATUS current
			DESCRIPTION
				"Module AAC3008C01V1 Entry"
			INDEX { aac3008c01v1Index }
			::= { aac3008c01v1Table 1 }

			Aac3008c01v1Entry ::=
			SEQUENCE {
				aac3008c01v1Index
				ModuleIndex,
				aac3008c01v1InputRef
				AudioRef2,
				aac3008c01v1SamplingFreq
				AudioSelFreq7,
				aac3008c01v1Bits
				Bit020124,
				aac3008c01v1Mode
				Bit0Aut1Man,
				aac3008c01v1FixDelay1
				DelaySamp3,
				aac3008c01v1FixDelay2
				DelaySamp3,
				aac3008c01v1FixDelay3
				DelaySamp3,
				aac3008c01v1FixDelay4
				DelaySamp3,
				aac3008c01v1GainAes1A
				Gain24dbMute,
				aac3008c01v1PhaseAes1A
				Bit0Nor1Inv,
				aac3008c01v1GainAes1B
				Gain24dbMute,
				aac3008c01v1PhaseAes1B
				Bit0Nor1Inv,
				aac3008c01v1GainAes2A
				Gain24dbMute,
				aac3008c01v1PhaseAes2A
				Bit0Nor1Inv,
				aac3008c01v1GainAes2B
				Gain24dbMute,
				aac3008c01v1PhaseAes2B
				Bit0Nor1Inv,
				aac3008c01v1GainAes3A
				Gain24dbMute,
				aac3008c01v1PhaseAes3A
				Bit0Nor1Inv,
				aac3008c01v1GainAes3B
				Gain24dbMute,
				aac3008c01v1PhaseAes3B
				Bit0Nor1Inv,
				aac3008c01v1GainAes4A
				Gain24dbMute,
				aac3008c01v1PhaseAes4A
				Bit0Nor1Inv,
				aac3008c01v1GainAes4B
				Gain24dbMute,
				aac3008c01v1PhaseAes4B
				Bit0Nor1Inv,
				aac3008c01v1MuteAes1A
				Bit0No1Yes,
				aac3008c01v1MuteAes1B
				Bit0No1Yes,
				aac3008c01v1MuteAes2A
				Bit0No1Yes,
				aac3008c01v1MuteAes2B
				Bit0No1Yes,
				aac3008c01v1MuteAes3A
				Bit0No1Yes,
				aac3008c01v1MuteAes3B
				Bit0No1Yes,
				aac3008c01v1MuteAes4A
				Bit0No1Yes,
				aac3008c01v1MuteAes4B
				Bit0No1Yes,
				aac3008c01v1InputLevel
				LevelDbu,
				aac3008c01v1OvldLevel
				LevelDbfs1,
				aac3008c01v1LockVid
				Bit0No1Yes,
				aac3008c01v1LockAes
				Bit0No1Yes,
				aac3008c01v1LockWclk
				Bit0No1Yes,
				aac3008c01v1VarDelay
				DelaySamp1,
				aac3008c01v1ClipCh1
				BitFail,
				aac3008c01v1OvlCh1
				BitFail,
				aac3008c01v1ClipCh2
				BitFail,
				aac3008c01v1OvlCh2
				BitFail,
				aac3008c01v1ClipCh3
				BitFail,
				aac3008c01v1OvlCh3
				BitFail,
				aac3008c01v1ClipCh4
				BitFail,
				aac3008c01v1OvlCh4
				BitFail,
				aac3008c01v1PeakLevOut1A
				LevelDbfs1,
				aac3008c01v1PeakLevOut1B
				LevelDbfs1,
				aac3008c01v1PeakLevOut2A
				LevelDbfs1,
				aac3008c01v1PeakLevOut2B
				LevelDbfs1,
				aac3008c01v1PeakLevOut3A
				LevelDbfs1,
				aac3008c01v1PeakLevOut3B
				LevelDbfs1,
				aac3008c01v1PeakLevOut4A
				LevelDbfs1,
				aac3008c01v1PeakLevOut4B
				LevelDbfs1,
				aac3008c01v1SerialNo
				SerialNo,
				aac3008c01v1Det525
				DetBb525,
				aac3008c01v1Det625
				DetBb625,
				aac3008c01v1AesDetFreq
				AudioSelFreq4,
				aac3008c01v1WclkDetFreq
				AudioSelFreq4
			 }

		-- 1.3.6.1.4.1.10106.3.101291.1.1.1
		aac3008c01v1Index OBJECT-TYPE
			SYNTAX ModuleIndex
			MAX-ACCESS read-only
			STATUS current
			DESCRIPTION
				"Index of AAC3008C01V1 Table"
		::= { aac3008c01v1Entry 1 }

		-- 1.3.6.1.4.1.10106.3.101291.1.1.3
		aac3008c01v1InputRef OBJECT-TYPE
			SYNTAX AudioRef2
			MAX-ACCESS read-write
			STATUS current
			DESCRIPTION
				"Allows selecting the reference input in manual mode"
		::= { aac3008c01v1Entry 3 }

		-- 1.3.6.1.4.1.10106.3.101291.1.1.5
		aac3008c01v1SamplingFreq OBJECT-TYPE
			SYNTAX AudioSelFreq7
			MAX-ACCESS read-write
			STATUS current
			DESCRIPTION
				"Allows selecting the output samplign frequency in manual mode"
		::= { aac3008c01v1Entry 5 }

		-- 1.3.6.1.4.1.10106.3.101291.1.1.7
		aac3008c01v1Bits OBJECT-TYPE
			SYNTAX Bit020124
			MAX-ACCESS read-write
			STATUS current
			DESCRIPTION
				"Allows selecting the number of bits of AES outputs"
		::= { aac3008c01v1Entry 7 }

		-- 1.3.6.1.4.1.10106.3.101291.1.1.9
		aac3008c01v1Mode OBJECT-TYPE
			SYNTAX Bit0Aut1Man
			MAX-ACCESS read-write
			STATUS current
			DESCRIPTION
				"Allows selecting the reference selection mode"
		::= { aac3008c01v1Entry 9 }

		-- 1.3.6.1.4.1.10106.3.101291.1.1.11
		aac3008c01v1FixDelay1 OBJECT-TYPE
			SYNTAX DelaySamp3
			MAX-ACCESS read-write
			STATUS current
			DESCRIPTION
				"Allows setting a fixed delay for AES1"
		::= { aac3008c01v1Entry 11 }

		-- 1.3.6.1.4.1.10106.3.101291.1.1.13
		aac3008c01v1FixDelay2 OBJECT-TYPE
			SYNTAX DelaySamp3
			MAX-ACCESS read-write
			STATUS current
			DESCRIPTION
				"Allows setting a fixed delay for AES2"
		::= { aac3008c01v1Entry 13 }

		-- 1.3.6.1.4.1.10106.3.101291.1.1.15
		aac3008c01v1FixDelay3 OBJECT-TYPE
			SYNTAX DelaySamp3
			MAX-ACCESS read-write
			STATUS current
			DESCRIPTION
				"Allows setting a fixed delay for AES3"
		::= { aac3008c01v1Entry 15 }

		-- 1.3.6.1.4.1.10106.3.101291.1.1.17
		aac3008c01v1FixDelay4 OBJECT-TYPE
			SYNTAX DelaySamp3
			MAX-ACCESS read-write
			STATUS current
			DESCRIPTION
				"Allows setting a fixed delay for AES4"
		::= { aac3008c01v1Entry 17 }

		-- 1.3.6.1.4.1.10106.3.101291.1.1.19
		aac3008c01v1GainAes1A OBJECT-TYPE
			SYNTAX Gain24dbMute
			MAX-ACCESS read-write
			STATUS current
			DESCRIPTION
				"Allows adjusting the gain of AES1 channel A"
		::= { aac3008c01v1Entry 19 }

		-- 1.3.6.1.4.1.10106.3.101291.1.1.21
		aac3008c01v1PhaseAes1A OBJECT-TYPE
			SYNTAX Bit0Nor1Inv
			MAX-ACCESS read-write
			STATUS current
			DESCRIPTION
				"Allows changing the phase of AES1 channel A"
		::= { aac3008c01v1Entry 21 }

		-- 1.3.6.1.4.1.10106.3.101291.1.1.23
		aac3008c01v1GainAes1B OBJECT-TYPE
			SYNTAX Gain24dbMute
			MAX-ACCESS read-write
			STATUS current
			DESCRIPTION
				"Allows adjusting the gain of AES1 channel B"
		::= { aac3008c01v1Entry 23 }

		-- 1.3.6.1.4.1.10106.3.101291.1.1.25
		aac3008c01v1PhaseAes1B OBJECT-TYPE
			SYNTAX Bit0Nor1Inv
			MAX-ACCESS read-write
			STATUS current
			DESCRIPTION
				"Allows changing the phase of AES1 channel B"
		::= { aac3008c01v1Entry 25 }

		-- 1.3.6.1.4.1.10106.3.101291.1.1.27
		aac3008c01v1GainAes2A OBJECT-TYPE
			SYNTAX Gain24dbMute
			MAX-ACCESS read-write
			STATUS current
			DESCRIPTION
				"Allows adjusting the gain of AES2 channel A"
		::= { aac3008c01v1Entry 27 }

		-- 1.3.6.1.4.1.10106.3.101291.1.1.29
		aac3008c01v1PhaseAes2A OBJECT-TYPE
			SYNTAX Bit0Nor1Inv
			MAX-ACCESS read-write
			STATUS current
			DESCRIPTION
				"Allows changing the phase of AES2 channel A"
		::= { aac3008c01v1Entry 29 }

		-- 1.3.6.1.4.1.10106.3.101291.1.1.31
		aac3008c01v1GainAes2B OBJECT-TYPE
			SYNTAX Gain24dbMute
			MAX-ACCESS read-write
			STATUS current
			DESCRIPTION
				"Allows adjusting the gain of AES2 channel B"
		::= { aac3008c01v1Entry 31 }

		-- 1.3.6.1.4.1.10106.3.101291.1.1.33
		aac3008c01v1PhaseAes2B OBJECT-TYPE
			SYNTAX Bit0Nor1Inv
			MAX-ACCESS read-write
			STATUS current
			DESCRIPTION
				"Allows changing the phase of AES2 channel B"
		::= { aac3008c01v1Entry 33 }

		-- 1.3.6.1.4.1.10106.3.101291.1.1.35
		aac3008c01v1GainAes3A OBJECT-TYPE
			SYNTAX Gain24dbMute
			MAX-ACCESS read-write
			STATUS current
			DESCRIPTION
				"Allows adjusting the gain of AES3 channel A"
		::= { aac3008c01v1Entry 35 }

		-- 1.3.6.1.4.1.10106.3.101291.1.1.37
		aac3008c01v1PhaseAes3A OBJECT-TYPE
			SYNTAX Bit0Nor1Inv
			MAX-ACCESS read-write
			STATUS current
			DESCRIPTION
				"Allows changing the phase of AES3 channel A"
		::= { aac3008c01v1Entry 37 }

		-- 1.3.6.1.4.1.10106.3.101291.1.1.39
		aac3008c01v1GainAes3B OBJECT-TYPE
			SYNTAX Gain24dbMute
			MAX-ACCESS read-write
			STATUS current
			DESCRIPTION
				"Allows adjusting the gain of AES3 channel B"
		::= { aac3008c01v1Entry 39 }

		-- 1.3.6.1.4.1.10106.3.101291.1.1.41
		aac3008c01v1PhaseAes3B OBJECT-TYPE
			SYNTAX Bit0Nor1Inv
			MAX-ACCESS read-write
			STATUS current
			DESCRIPTION
				"Allows changing the phase of AES3 channel B"
		::= { aac3008c01v1Entry 41 }

		-- 1.3.6.1.4.1.10106.3.101291.1.1.43
		aac3008c01v1GainAes4A OBJECT-TYPE
			SYNTAX Gain24dbMute
			MAX-ACCESS read-write
			STATUS current
			DESCRIPTION
				"Allows adjusting the gain of AES4 channel A"
		::= { aac3008c01v1Entry 43 }

		-- 1.3.6.1.4.1.10106.3.101291.1.1.45
		aac3008c01v1PhaseAes4A OBJECT-TYPE
			SYNTAX Bit0Nor1Inv
			MAX-ACCESS read-write
			STATUS current
			DESCRIPTION
				"Allows changing the phase of AES4 channel A"
		::= { aac3008c01v1Entry 45 }

		-- 1.3.6.1.4.1.10106.3.101291.1.1.47
		aac3008c01v1GainAes4B OBJECT-TYPE
			SYNTAX Gain24dbMute
			MAX-ACCESS read-write
			STATUS current
			DESCRIPTION
				"Allows adjusting the gain of AES4 channel B"
		::= { aac3008c01v1Entry 47 }

		-- 1.3.6.1.4.1.10106.3.101291.1.1.49
		aac3008c01v1PhaseAes4B OBJECT-TYPE
			SYNTAX Bit0Nor1Inv
			MAX-ACCESS read-write
			STATUS current
			DESCRIPTION
				"Allows changing the phase of AES4 channel B"
		::= { aac3008c01v1Entry 49 }

		-- 1.3.6.1.4.1.10106.3.101291.1.1.51
		aac3008c01v1MuteAes1A OBJECT-TYPE
			SYNTAX Bit0No1Yes
			MAX-ACCESS read-write
			STATUS current
			DESCRIPTION
				"Allows muting AES1 channel A"
		::= { aac3008c01v1Entry 51 }

		-- 1.3.6.1.4.1.10106.3.101291.1.1.53
		aac3008c01v1MuteAes1B OBJECT-TYPE
			SYNTAX Bit0No1Yes
			MAX-ACCESS read-write
			STATUS current
			DESCRIPTION
				"Allows muting AES1 channel B"
		::= { aac3008c01v1Entry 53 }

		-- 1.3.6.1.4.1.10106.3.101291.1.1.55
		aac3008c01v1MuteAes2A OBJECT-TYPE
			SYNTAX Bit0No1Yes
			MAX-ACCESS read-write
			STATUS current
			DESCRIPTION
				"Allows muting AES2 channel A"
		::= { aac3008c01v1Entry 55 }

		-- 1.3.6.1.4.1.10106.3.101291.1.1.57
		aac3008c01v1MuteAes2B OBJECT-TYPE
			SYNTAX Bit0No1Yes
			MAX-ACCESS read-write
			STATUS current
			DESCRIPTION
				"Allows muting AES2 channel B"
		::= { aac3008c01v1Entry 57 }

		-- 1.3.6.1.4.1.10106.3.101291.1.1.59
		aac3008c01v1MuteAes3A OBJECT-TYPE
			SYNTAX Bit0No1Yes
			MAX-ACCESS read-write
			STATUS current
			DESCRIPTION
				"Allows muting AES3 channel A"
		::= { aac3008c01v1Entry 59 }

		-- 1.3.6.1.4.1.10106.3.101291.1.1.61
		aac3008c01v1MuteAes3B OBJECT-TYPE
			SYNTAX Bit0No1Yes
			MAX-ACCESS read-write
			STATUS current
			DESCRIPTION
				"Allows muting AES3 channel B"
		::= { aac3008c01v1Entry 61 }

		-- 1.3.6.1.4.1.10106.3.101291.1.1.63
		aac3008c01v1MuteAes4A OBJECT-TYPE
			SYNTAX Bit0No1Yes
			MAX-ACCESS read-write
			STATUS current
			DESCRIPTION
				"Allows muting AES4 channel A"
		::= { aac3008c01v1Entry 63 }

		-- 1.3.6.1.4.1.10106.3.101291.1.1.65
		aac3008c01v1MuteAes4B OBJECT-TYPE
			SYNTAX Bit0No1Yes
			MAX-ACCESS read-write
			STATUS current
			DESCRIPTION
				"Allows muting AES4 channel B"
		::= { aac3008c01v1Entry 65 }

		-- 1.3.6.1.4.1.10106.3.101291.1.1.67
		aac3008c01v1InputLevel OBJECT-TYPE
			SYNTAX LevelDbu
			MAX-ACCESS read-write
			STATUS current
			DESCRIPTION
				"Allows selecting the audio full scale level"
		::= { aac3008c01v1Entry 67 }

		-- 1.3.6.1.4.1.10106.3.101291.1.1.69
		aac3008c01v1OvldLevel OBJECT-TYPE
			SYNTAX LevelDbfs1
			MAX-ACCESS read-write
			STATUS current
			DESCRIPTION
				"Allows adjusting the threshold level for the overload detector"
		::= { aac3008c01v1Entry 69 }

		-- 1.3.6.1.4.1.10106.3.101291.1.1.71
		aac3008c01v1LockVid OBJECT-TYPE
			SYNTAX Bit0No1Yes
			MAX-ACCESS read-only
			STATUS current
			DESCRIPTION
				"Indicates video reference lock"
		::= { aac3008c01v1Entry 71 }

		-- 1.3.6.1.4.1.10106.3.101291.1.1.73
		aac3008c01v1LockAes OBJECT-TYPE
			SYNTAX Bit0No1Yes
			MAX-ACCESS read-only
			STATUS current
			DESCRIPTION
				"Indicates AES reference lock"
		::= { aac3008c01v1Entry 73 }

		-- 1.3.6.1.4.1.10106.3.101291.1.1.75
		aac3008c01v1LockWclk OBJECT-TYPE
			SYNTAX Bit0No1Yes
			MAX-ACCESS read-only
			STATUS current
			DESCRIPTION
				"Indicates Wordclock reference lock"
		::= { aac3008c01v1Entry 75 }

		-- 1.3.6.1.4.1.10106.3.101291.1.1.77
		aac3008c01v1VarDelay OBJECT-TYPE
			SYNTAX DelaySamp1
			MAX-ACCESS read-only
			STATUS current
			DESCRIPTION
				"Inidcates variable delay"
		::= { aac3008c01v1Entry 77 }

		-- 1.3.6.1.4.1.10106.3.101291.1.1.79
		aac3008c01v1ClipCh1 OBJECT-TYPE
			SYNTAX BitFail
			MAX-ACCESS read-only
			STATUS current
			DESCRIPTION
				"Indicates channel 1A&1B clipping fail"
		::= { aac3008c01v1Entry 79 }

		-- 1.3.6.1.4.1.10106.3.101291.1.1.81
		aac3008c01v1OvlCh1 OBJECT-TYPE
			SYNTAX BitFail
			MAX-ACCESS read-only
			STATUS current
			DESCRIPTION
				"Indicates AES1 overload fail"
		::= { aac3008c01v1Entry 81 }

		-- 1.3.6.1.4.1.10106.3.101291.1.1.83
		aac3008c01v1ClipCh2 OBJECT-TYPE
			SYNTAX BitFail
			MAX-ACCESS read-only
			STATUS current
			DESCRIPTION
				"Indicates channel 2A&2B clipping fail"
		::= { aac3008c01v1Entry 83 }

		-- 1.3.6.1.4.1.10106.3.101291.1.1.85
		aac3008c01v1OvlCh2 OBJECT-TYPE
			SYNTAX BitFail
			MAX-ACCESS read-only
			STATUS current
			DESCRIPTION
				"Indicates AES2 overload fail"
		::= { aac3008c01v1Entry 85 }

		-- 1.3.6.1.4.1.10106.3.101291.1.1.87
		aac3008c01v1ClipCh3 OBJECT-TYPE
			SYNTAX BitFail
			MAX-ACCESS read-only
			STATUS current
			DESCRIPTION
				"Indicates channel 3A&3B clipping fail"
		::= { aac3008c01v1Entry 87 }

		-- 1.3.6.1.4.1.10106.3.101291.1.1.89
		aac3008c01v1OvlCh3 OBJECT-TYPE
			SYNTAX BitFail
			MAX-ACCESS read-only
			STATUS current
			DESCRIPTION
				"Indicates AES3 overload fail"
		::= { aac3008c01v1Entry 89 }

		-- 1.3.6.1.4.1.10106.3.101291.1.1.91
		aac3008c01v1ClipCh4 OBJECT-TYPE
			SYNTAX BitFail
			MAX-ACCESS read-only
			STATUS current
			DESCRIPTION
				"Indicates channel 4A&4B clipping fail"
		::= { aac3008c01v1Entry 91 }

		-- 1.3.6.1.4.1.10106.3.101291.1.1.93
		aac3008c01v1OvlCh4 OBJECT-TYPE
			SYNTAX BitFail
			MAX-ACCESS read-only
			STATUS current
			DESCRIPTION
				"Indicates AES4 overload fail"
		::= { aac3008c01v1Entry 93 }

		-- 1.3.6.1.4.1.10106.3.101291.1.1.95
		aac3008c01v1PeakLevOut1A OBJECT-TYPE
			SYNTAX LevelDbfs1
			MAX-ACCESS read-only
			STATUS current
			DESCRIPTION
				"AES1 channel A peak level"
		::= { aac3008c01v1Entry 95 }

		-- 1.3.6.1.4.1.10106.3.101291.1.1.97
		aac3008c01v1PeakLevOut1B OBJECT-TYPE
			SYNTAX LevelDbfs1
			MAX-ACCESS read-only
			STATUS current
			DESCRIPTION
				"AES1 channel B peak level"
		::= { aac3008c01v1Entry 97 }

		-- 1.3.6.1.4.1.10106.3.101291.1.1.99
		aac3008c01v1PeakLevOut2A OBJECT-TYPE
			SYNTAX LevelDbfs1
			MAX-ACCESS read-only
			STATUS current
			DESCRIPTION
				"AES2 channel A peak level"
		::= { aac3008c01v1Entry 99 }

		-- 1.3.6.1.4.1.10106.3.101291.1.1.101
		aac3008c01v1PeakLevOut2B OBJECT-TYPE
			SYNTAX LevelDbfs1
			MAX-ACCESS read-only
			STATUS current
			DESCRIPTION
				"AES2 channel B peak level"
		::= { aac3008c01v1Entry 101 }

		-- 1.3.6.1.4.1.10106.3.101291.1.1.103
		aac3008c01v1PeakLevOut3A OBJECT-TYPE
			SYNTAX LevelDbfs1
			MAX-ACCESS read-only
			STATUS current
			DESCRIPTION
				"AES3 channel A peak level"
		::= { aac3008c01v1Entry 103 }

		-- 1.3.6.1.4.1.10106.3.101291.1.1.105
		aac3008c01v1PeakLevOut3B OBJECT-TYPE
			SYNTAX LevelDbfs1
			MAX-ACCESS read-only
			STATUS current
			DESCRIPTION
				"AES3 channel B peak level"
		::= { aac3008c01v1Entry 105 }

		-- 1.3.6.1.4.1.10106.3.101291.1.1.107
		aac3008c01v1PeakLevOut4A OBJECT-TYPE
			SYNTAX LevelDbfs1
			MAX-ACCESS read-only
			STATUS current
			DESCRIPTION
				"AES4 channel A peak level"
		::= { aac3008c01v1Entry 107 }

		-- 1.3.6.1.4.1.10106.3.101291.1.1.109
		aac3008c01v1PeakLevOut4B OBJECT-TYPE
			SYNTAX LevelDbfs1
			MAX-ACCESS read-only
			STATUS current
			DESCRIPTION
				"AES4 channel B peak level"
		::= { aac3008c01v1Entry 109 }

		-- 1.3.6.1.4.1.10106.3.101291.1.1.111
		aac3008c01v1SerialNo OBJECT-TYPE
			SYNTAX SerialNo
			MAX-ACCESS read-only
			STATUS current
			DESCRIPTION
				"Serial number"
		::= { aac3008c01v1Entry 111 }

		-- 1.3.6.1.4.1.10106.3.101291.1.1.113
		aac3008c01v1Det525 OBJECT-TYPE
			SYNTAX DetBb525
			MAX-ACCESS read-only
			STATUS current
			DESCRIPTION
				"525 lines signal detected"
		::= { aac3008c01v1Entry 113 }

		-- 1.3.6.1.4.1.10106.3.101291.1.1.115
		aac3008c01v1Det625 OBJECT-TYPE
			SYNTAX DetBb625
			MAX-ACCESS read-only
			STATUS current
			DESCRIPTION
				"625 lines signal detected"
		::= { aac3008c01v1Entry 115 }

		-- 1.3.6.1.4.1.10106.3.101291.1.1.117
		aac3008c01v1AesDetFreq OBJECT-TYPE
			SYNTAX AudioSelFreq4
			MAX-ACCESS read-only
			STATUS current
			DESCRIPTION
				"Indicates the AES reference detected frequency"
		::= { aac3008c01v1Entry 117 }

		-- 1.3.6.1.4.1.10106.3.101291.1.1.119
		aac3008c01v1WclkDetFreq OBJECT-TYPE
			SYNTAX AudioSelFreq4
			MAX-ACCESS read-only
			STATUS current
			DESCRIPTION
				"Indicates tje Wordclock reference detected frequency"
		::= { aac3008c01v1Entry 119 }

		-- 1.3.6.1.4.1.10106.3.315301
		dsw3000c05v1 OBJECT IDENTIFIER ::= { albalaProducts 315301 }

		-- 1.3.6.1.4.1.10106.3.315301.1
		dsw3000c05v1Table  OBJECT-TYPE
			SYNTAX SEQUENCE OF Dsw3000c05v1Entry
			MAX-ACCESS not-accessible
			STATUS current
			DESCRIPTION
				"Module  DSW3000C05V1 Table"
			::= { dsw3000c05v1 1 }

		-- 1.3.6.1.4.1.10106.3.315301.1.1
		dsw3000c05v1Entry  OBJECT-TYPE
			SYNTAX Dsw3000c05v1Entry
			MAX-ACCESS not-accessible
			STATUS current
			DESCRIPTION
				"Module DSW3000C05V1 Entry"
			INDEX { dsw3000c05v1Index }
			::= { dsw3000c05v1Table 1 }

			Dsw3000c05v1Entry ::=
			SEQUENCE {
				dsw3000c05v1Index
				ModuleIndex,
				dsw3000c05v1Mode
				ChgOverMode2,
				dsw3000c05v1ModeTrapEnable
				AlarmEnable,
				dsw3000c05v1Buzzer
				BitMask,
				dsw3000c05v1Input
				ChgOverInput1,
				dsw3000c05v1InputTrapEnable
				AlarmEnable,
				dsw3000c05v1MainFail
				BitFail,
				dsw3000c05v1MainFailTrapEnable
				AlarmEnable,
				dsw3000c05v1ExtMainFail
				BitFail,
				dsw3000c05v1ExtMainFailTrapEnable
				AlarmEnable,
				dsw3000c05v1ResFail
				BitFail,
				dsw3000c05v1ResFailTrapEnable
				AlarmEnable,
				dsw3000c05v1ExtResFail
				BitFail,
				dsw3000c05v1ExtResFailTrapEnable
				AlarmEnable,
				dsw3000c05v1AuxFail
				BitFail,
				dsw3000c05v1AuxFailTrapEnable
				AlarmEnable,
				dsw3000c05v1ExtAuxFail
				BitFail,
				dsw3000c05v1ExtAuxFailTrapEnable
				AlarmEnable
			 }

		-- 1.3.6.1.4.1.10106.3.101291.1.1.1
		dsw3000c05v1Index OBJECT-TYPE
			SYNTAX ModuleIndex
			MAX-ACCESS read-only
			STATUS current
			DESCRIPTION
				"Index of DSW3000C05V1 Table"
		::= { dsw3000c05v1Entry 1 }

		-- 1.3.6.1.4.1.10106.3.101291.1.1.3
		dsw3000c05v1Mode OBJECT-TYPE
			SYNTAX ChgOverMode2
			MAX-ACCESS read-write
			STATUS current
			DESCRIPTION
				"Allows selecting the switching mode"
		::= { dsw3000c05v1Entry 3 }

		-- 1.3.6.1.4.1.10106.3.101291.1.1.4
		dsw3000c05v1ModeTrapEnable OBJECT-TYPE
			SYNTAX AlarmEnable
			MAX-ACCESS read-write
			STATUS current
			DESCRIPTION
				"Allows selecting the switching mode Trap Enable"
		::= { dsw3000c05v1Entry 4 }

		-- 1.3.6.1.4.1.10106.3.101291.1.1.5
		dsw3000c05v1Buzzer OBJECT-TYPE
			SYNTAX BitMask
			MAX-ACCESS read-write
			STATUS current
			DESCRIPTION
				"Allows buzzer operation"
		::= { dsw3000c05v1Entry 5 }

		-- 1.3.6.1.4.1.10106.3.101291.1.1.7
		dsw3000c05v1Input OBJECT-TYPE
			SYNTAX ChgOverInput1
			MAX-ACCESS read-write
			STATUS current
			DESCRIPTION
				"Selected input"
		::= { dsw3000c05v1Entry 7 }

		-- 1.3.6.1.4.1.10106.3.101291.1.1.8
		dsw3000c05v1InputTrapEnable OBJECT-TYPE
			SYNTAX AlarmEnable
			MAX-ACCESS read-write
			STATUS current
			DESCRIPTION
				"Selected input Trap Enable"
		::= { dsw3000c05v1Entry 8 }

		-- 1.3.6.1.4.1.10106.3.101291.1.1.9
		dsw3000c05v1MainFail OBJECT-TYPE
			SYNTAX BitFail
			MAX-ACCESS read-only
			STATUS current
			DESCRIPTION
				"Main input status"
		::= { dsw3000c05v1Entry 9 }

		-- 1.3.6.1.4.1.10106.3.101291.1.1.10
		dsw3000c05v1MainFailTrapEnable OBJECT-TYPE
			SYNTAX AlarmEnable
			MAX-ACCESS read-write
			STATUS current
			DESCRIPTION
				"Main input status Trap Enable"
		::= { dsw3000c05v1Entry 10 }

		-- 1.3.6.1.4.1.10106.3.101291.1.1.11
		dsw3000c05v1ExtMainFail OBJECT-TYPE
			SYNTAX BitFail
			MAX-ACCESS read-only
			STATUS current
			DESCRIPTION
				"Main external input fail status"
		::= { dsw3000c05v1Entry 11 }

		-- 1.3.6.1.4.1.10106.3.101291.1.1.12
		dsw3000c05v1ExtMainFailTrapEnable OBJECT-TYPE
			SYNTAX AlarmEnable
			MAX-ACCESS read-write
			STATUS current
			DESCRIPTION
				"Main external input fail status Trap Enable"
		::= { dsw3000c05v1Entry 12 }

		-- 1.3.6.1.4.1.10106.3.101291.1.1.13
		dsw3000c05v1ResFail OBJECT-TYPE
			SYNTAX BitFail
			MAX-ACCESS read-only
			STATUS current
			DESCRIPTION
				"Reserve input status"
		::= { dsw3000c05v1Entry 13 }

		-- 1.3.6.1.4.1.10106.3.101291.1.1.14
		dsw3000c05v1ResFailTrapEnable OBJECT-TYPE
			SYNTAX AlarmEnable
			MAX-ACCESS read-write
			STATUS current
			DESCRIPTION
				"Reserve input status Trap Enable"
		::= { dsw3000c05v1Entry 14 }

		-- 1.3.6.1.4.1.10106.3.101291.1.1.15
		dsw3000c05v1ExtResFail OBJECT-TYPE
			SYNTAX BitFail
			MAX-ACCESS read-only
			STATUS current
			DESCRIPTION
				"Reserve external input fail status"
		::= { dsw3000c05v1Entry 15 }

		-- 1.3.6.1.4.1.10106.3.101291.1.1.16
		dsw3000c05v1ExtResFailTrapEnable OBJECT-TYPE
			SYNTAX AlarmEnable
			MAX-ACCESS read-write
			STATUS current
			DESCRIPTION
				"Reserve external input fail status Trap Enable"
		::= { dsw3000c05v1Entry 16 }

		-- 1.3.6.1.4.1.10106.3.101291.1.1.17
		dsw3000c05v1AuxFail OBJECT-TYPE
			SYNTAX BitFail
			MAX-ACCESS read-only
			STATUS current
			DESCRIPTION
				"Auxiliar input status"
		::= { dsw3000c05v1Entry 17 }

		-- 1.3.6.1.4.1.10106.3.101291.1.1.18
		dsw3000c05v1AuxFailTrapEnable OBJECT-TYPE
			SYNTAX AlarmEnable
			MAX-ACCESS read-write
			STATUS current
			DESCRIPTION
				"Auxiliar input status Trap Enable"
		::= { dsw3000c05v1Entry 18 }

		-- 1.3.6.1.4.1.10106.3.101291.1.1.19
		dsw3000c05v1ExtAuxFail OBJECT-TYPE
			SYNTAX BitFail
			MAX-ACCESS read-only
			STATUS current
			DESCRIPTION
				"Auxiliar external input fail status"
		::= { dsw3000c05v1Entry 19 }

		-- 1.3.6.1.4.1.10106.3.101291.1.1.20
		dsw3000c05v1ExtAuxFailTrapEnable OBJECT-TYPE
			SYNTAX AlarmEnable
			MAX-ACCESS read-write
			STATUS current
			DESCRIPTION
				"Auxiliar external input fail status Trap Enable"
		::= { dsw3000c05v1Entry 20 }

		-- 1.3.6.1.4.1.10106.3.316801
		ssw3000c01v1 OBJECT IDENTIFIER ::= { albalaProducts 316801 }

		-- 1.3.6.1.4.1.10106.3.316801.1
		ssw3000c01v1Table  OBJECT-TYPE
			SYNTAX SEQUENCE OF Ssw3000c01v1Entry
			MAX-ACCESS not-accessible
			STATUS current
			DESCRIPTION
				"Module  SSW3000C01V1 Table"
			::= { ssw3000c01v1 1 }

		-- 1.3.6.1.4.1.10106.3.316801.1.1
		ssw3000c01v1Entry  OBJECT-TYPE
			SYNTAX Ssw3000c01v1Entry
			MAX-ACCESS not-accessible
			STATUS current
			DESCRIPTION
				"Module SSW3000C01V1 Entry"
			INDEX { ssw3000c01v1Index }
			::= { ssw3000c01v1Table 1 }

			Ssw3000c01v1Entry ::=
			SEQUENCE {
				ssw3000c01v1Index
				ModuleIndex,
				ssw3000c01v1Mode
				ChgOverMode2,
				ssw3000c01v1ModeTrapEnable
				AlarmEnable,
				ssw3000c01v1Buzzer
				BitMask,
				ssw3000c01v1DvbTMode
				Bit0No1Yes,
				ssw3000c01v1DvbTModeTrapEnable
				AlarmEnable,
				ssw3000c01v1Input
				ChgOverInput1,
				ssw3000c01v1InputTrapEnable
				AlarmEnable,
				ssw3000c01v1InputChange
				Bit0No1Yes,
				ssw3000c01v1OutDelay
				DelayX100Ns,
				ssw3000c01v1OutDelayTrapEnable
				AlarmEnable,
				ssw3000c01v1MainFail
				BitFail,
				ssw3000c01v1MainFailTrapEnable
				AlarmEnable,
				ssw3000c01v1ExtMainFail
				BitFail,
				ssw3000c01v1ExtMainFailTrapEnable
				AlarmEnable,
				ssw3000c01v1ResFail
				BitFail,
				ssw3000c01v1ResFailTrapEnable
				AlarmEnable,
				ssw3000c01v1ExtResFail
				BitFail,
				ssw3000c01v1ExtResFailTrapEnable
				AlarmEnable,
				ssw3000c01v1AuxFail
				BitFail,
				ssw3000c01v1AuxFailTrapEnable
				AlarmEnable,
				ssw3000c01v1ExtAuxFail
				BitFail,
				ssw3000c01v1ExtAuxFailTrapEnable
				AlarmEnable,
				ssw3000c01v11ppsFail
				BitFail,
				ssw3000c01v11ppsFailTrapEnable
				AlarmEnable,
				ssw3000c01v1MainResSeam
				Bit0Sea1Nse,
				ssw3000c01v1ResAuxSeam
				Bit0Sea1Nse,
				ssw3000c01v1MainAuxSeam
				Bit0Sea1Nse,
				ssw3000c01v1GlobalSeam
				Bit0Sea1Nse,
				ssw3000c01v1GlobalSeamTrapEnable
				AlarmEnable,
				ssw3000c01v1MainDelay
				DelayX100Ns,
				ssw3000c01v1ResDelay
				DelayX100Ns,
				ssw3000c01v1AuxDelay
				DelayX100Ns,
				ssw3000c01v1SerialNo
				SerialNo
			 }

		-- 1.3.6.1.4.1.10106.3.101291.1.1.1
		ssw3000c01v1Index OBJECT-TYPE
			SYNTAX ModuleIndex
			MAX-ACCESS read-only
			STATUS current
			DESCRIPTION
				"Index of SSW3000C01V1 Table"
		::= { ssw3000c01v1Entry 1 }

		-- 1.3.6.1.4.1.10106.3.101291.1.1.3
		ssw3000c01v1Mode OBJECT-TYPE
			SYNTAX ChgOverMode2
			MAX-ACCESS read-write
			STATUS current
			DESCRIPTION
				"Allows selecting the switching mode"
		::= { ssw3000c01v1Entry 3 }

		-- 1.3.6.1.4.1.10106.3.101291.1.1.4
		ssw3000c01v1ModeTrapEnable OBJECT-TYPE
			SYNTAX AlarmEnable
			MAX-ACCESS read-write
			STATUS current
			DESCRIPTION
				"Allows selecting the switching mode Trap Enable"
		::= { ssw3000c01v1Entry 4 }

		-- 1.3.6.1.4.1.10106.3.101291.1.1.5
		ssw3000c01v1Buzzer OBJECT-TYPE
			SYNTAX BitMask
			MAX-ACCESS read-write
			STATUS current
			DESCRIPTION
				"Allows buzzer operation"
		::= { ssw3000c01v1Entry 5 }

		-- 1.3.6.1.4.1.10106.3.101291.1.1.7
		ssw3000c01v1DvbTMode OBJECT-TYPE
			SYNTAX Bit0No1Yes
			MAX-ACCESS read-write
			STATUS current
			DESCRIPTION
				"Selects DVB-T mode. Seamless operation is only possible in DVB-T mode"
		::= { ssw3000c01v1Entry 7 }

		-- 1.3.6.1.4.1.10106.3.101291.1.1.8
		ssw3000c01v1DvbTModeTrapEnable OBJECT-TYPE
			SYNTAX AlarmEnable
			MAX-ACCESS read-write
			STATUS current
			DESCRIPTION
				"Selects DVB-T mode. Seamless operation is only possible in DVB-T mode Trap Enable"
		::= { ssw3000c01v1Entry 8 }

		-- 1.3.6.1.4.1.10106.3.101291.1.1.9
		ssw3000c01v1Input OBJECT-TYPE
			SYNTAX ChgOverInput1
			MAX-ACCESS read-write
			STATUS current
			DESCRIPTION
				"Selected input"
		::= { ssw3000c01v1Entry 9 }

		-- 1.3.6.1.4.1.10106.3.101291.1.1.10
		ssw3000c01v1InputTrapEnable OBJECT-TYPE
			SYNTAX AlarmEnable
			MAX-ACCESS read-write
			STATUS current
			DESCRIPTION
				"Selected input Trap Enable"
		::= { ssw3000c01v1Entry 10 }

		-- 1.3.6.1.4.1.10106.3.101291.1.1.11
		ssw3000c01v1InputChange OBJECT-TYPE
			SYNTAX Bit0No1Yes
			MAX-ACCESS read-write
			STATUS current
			DESCRIPTION
				"Signals a change in selected input"
		::= { ssw3000c01v1Entry 11 }

		-- 1.3.6.1.4.1.10106.3.101291.1.1.13
		ssw3000c01v1OutDelay OBJECT-TYPE
			SYNTAX DelayX100Ns
			MAX-ACCESS read-write
			STATUS current
			DESCRIPTION
				"Output delay refered to 1PPS reference"
		::= { ssw3000c01v1Entry 13 }

		-- 1.3.6.1.4.1.10106.3.101291.1.1.14
		ssw3000c01v1OutDelayTrapEnable OBJECT-TYPE
			SYNTAX AlarmEnable
			MAX-ACCESS read-write
			STATUS current
			DESCRIPTION
				"Output delay refered to 1PPS reference Trap Enable"
		::= { ssw3000c01v1Entry 14 }

		-- 1.3.6.1.4.1.10106.3.101291.1.1.15
		ssw3000c01v1MainFail OBJECT-TYPE
			SYNTAX BitFail
			MAX-ACCESS read-only
			STATUS current
			DESCRIPTION
				"Main input status"
		::= { ssw3000c01v1Entry 15 }

		-- 1.3.6.1.4.1.10106.3.101291.1.1.16
		ssw3000c01v1MainFailTrapEnable OBJECT-TYPE
			SYNTAX AlarmEnable
			MAX-ACCESS read-write
			STATUS current
			DESCRIPTION
				"Main input status Trap Enable"
		::= { ssw3000c01v1Entry 16 }

		-- 1.3.6.1.4.1.10106.3.101291.1.1.17
		ssw3000c01v1ExtMainFail OBJECT-TYPE
			SYNTAX BitFail
			MAX-ACCESS read-only
			STATUS current
			DESCRIPTION
				"Main external input fail status"
		::= { ssw3000c01v1Entry 17 }

		-- 1.3.6.1.4.1.10106.3.101291.1.1.18
		ssw3000c01v1ExtMainFailTrapEnable OBJECT-TYPE
			SYNTAX AlarmEnable
			MAX-ACCESS read-write
			STATUS current
			DESCRIPTION
				"Main external input fail status Trap Enable"
		::= { ssw3000c01v1Entry 18 }

		-- 1.3.6.1.4.1.10106.3.101291.1.1.19
		ssw3000c01v1ResFail OBJECT-TYPE
			SYNTAX BitFail
			MAX-ACCESS read-only
			STATUS current
			DESCRIPTION
				"Reserve input status"
		::= { ssw3000c01v1Entry 19 }

		-- 1.3.6.1.4.1.10106.3.101291.1.1.20
		ssw3000c01v1ResFailTrapEnable OBJECT-TYPE
			SYNTAX AlarmEnable
			MAX-ACCESS read-write
			STATUS current
			DESCRIPTION
				"Reserve input status Trap Enable"
		::= { ssw3000c01v1Entry 20 }

		-- 1.3.6.1.4.1.10106.3.101291.1.1.21
		ssw3000c01v1ExtResFail OBJECT-TYPE
			SYNTAX BitFail
			MAX-ACCESS read-only
			STATUS current
			DESCRIPTION
				"Reserve external input fail status"
		::= { ssw3000c01v1Entry 21 }

		-- 1.3.6.1.4.1.10106.3.101291.1.1.22
		ssw3000c01v1ExtResFailTrapEnable OBJECT-TYPE
			SYNTAX AlarmEnable
			MAX-ACCESS read-write
			STATUS current
			DESCRIPTION
				"Reserve external input fail status Trap Enable"
		::= { ssw3000c01v1Entry 22 }

		-- 1.3.6.1.4.1.10106.3.101291.1.1.23
		ssw3000c01v1AuxFail OBJECT-TYPE
			SYNTAX BitFail
			MAX-ACCESS read-only
			STATUS current
			DESCRIPTION
				"Auxiliar input status"
		::= { ssw3000c01v1Entry 23 }

		-- 1.3.6.1.4.1.10106.3.101291.1.1.24
		ssw3000c01v1AuxFailTrapEnable OBJECT-TYPE
			SYNTAX AlarmEnable
			MAX-ACCESS read-write
			STATUS current
			DESCRIPTION
				"Auxiliar input status Trap Enable"
		::= { ssw3000c01v1Entry 24 }

		-- 1.3.6.1.4.1.10106.3.101291.1.1.25
		ssw3000c01v1ExtAuxFail OBJECT-TYPE
			SYNTAX BitFail
			MAX-ACCESS read-only
			STATUS current
			DESCRIPTION
				"Auxiliar external input fail status"
		::= { ssw3000c01v1Entry 25 }

		-- 1.3.6.1.4.1.10106.3.101291.1.1.26
		ssw3000c01v1ExtAuxFailTrapEnable OBJECT-TYPE
			SYNTAX AlarmEnable
			MAX-ACCESS read-write
			STATUS current
			DESCRIPTION
				"Auxiliar external input fail status Trap Enable"
		::= { ssw3000c01v1Entry 26 }

		-- 1.3.6.1.4.1.10106.3.101291.1.1.27
		ssw3000c01v11ppsFail OBJECT-TYPE
			SYNTAX BitFail
			MAX-ACCESS read-only
			STATUS current
			DESCRIPTION
				"1PPS reference input status"
		::= { ssw3000c01v1Entry 27 }

		-- 1.3.6.1.4.1.10106.3.101291.1.1.28
		ssw3000c01v11ppsFailTrapEnable OBJECT-TYPE
			SYNTAX AlarmEnable
			MAX-ACCESS read-write
			STATUS current
			DESCRIPTION
				"1PPS reference input status Trap Enable"
		::= { ssw3000c01v1Entry 28 }

		-- 1.3.6.1.4.1.10106.3.101291.1.1.29
		ssw3000c01v1MainResSeam OBJECT-TYPE
			SYNTAX Bit0Sea1Nse
			MAX-ACCESS read-only
			STATUS current
			DESCRIPTION
				"Main to reserve seamles switching capability"
		::= { ssw3000c01v1Entry 29 }

		-- 1.3.6.1.4.1.10106.3.101291.1.1.31
		ssw3000c01v1ResAuxSeam OBJECT-TYPE
			SYNTAX Bit0Sea1Nse
			MAX-ACCESS read-only
			STATUS current
			DESCRIPTION
				"Reserve to auxiliar seamles switching capability"
		::= { ssw3000c01v1Entry 31 }

		-- 1.3.6.1.4.1.10106.3.101291.1.1.33
		ssw3000c01v1MainAuxSeam OBJECT-TYPE
			SYNTAX Bit0Sea1Nse
			MAX-ACCESS read-only
			STATUS current
			DESCRIPTION
				"Main to auxiliar seamles switching capability"
		::= { ssw3000c01v1Entry 33 }

		-- 1.3.6.1.4.1.10106.3.101291.1.1.35
		ssw3000c01v1GlobalSeam OBJECT-TYPE
			SYNTAX Bit0Sea1Nse
			MAX-ACCESS read-only
			STATUS current
			DESCRIPTION
				"Global seamles switching capability"
		::= { ssw3000c01v1Entry 35 }

		-- 1.3.6.1.4.1.10106.3.101291.1.1.36
		ssw3000c01v1GlobalSeamTrapEnable OBJECT-TYPE
			SYNTAX AlarmEnable
			MAX-ACCESS read-write
			STATUS current
			DESCRIPTION
				"Global seamles switching capability Trap Enable"
		::= { ssw3000c01v1Entry 36 }

		-- 1.3.6.1.4.1.10106.3.101291.1.1.37
		ssw3000c01v1MainDelay OBJECT-TYPE
			SYNTAX DelayX100Ns
			MAX-ACCESS read-only
			STATUS current
			DESCRIPTION
				"Main input delay refered to 1PPS reference"
		::= { ssw3000c01v1Entry 37 }

		-- 1.3.6.1.4.1.10106.3.101291.1.1.39
		ssw3000c01v1ResDelay OBJECT-TYPE
			SYNTAX DelayX100Ns
			MAX-ACCESS read-only
			STATUS current
			DESCRIPTION
				"Reserve input delay refered to 1PPS reference"
		::= { ssw3000c01v1Entry 39 }

		-- 1.3.6.1.4.1.10106.3.101291.1.1.41
		ssw3000c01v1AuxDelay OBJECT-TYPE
			SYNTAX DelayX100Ns
			MAX-ACCESS read-only
			STATUS current
			DESCRIPTION
				"Auxiliar input delay refered to 1PPS reference"
		::= { ssw3000c01v1Entry 41 }

		-- 1.3.6.1.4.1.10106.3.101291.1.1.43
		ssw3000c01v1SerialNo OBJECT-TYPE
			SYNTAX SerialNo
			MAX-ACCESS read-only
			STATUS current
			DESCRIPTION
				"Serial number"
		::= { ssw3000c01v1Entry 43 }

		-- 1.3.6.1.4.1.10106.3.320501
		pdc3002c01v1 OBJECT IDENTIFIER ::= { albalaProducts 320501 }

		-- 1.3.6.1.4.1.10106.3.320501.1
		pdc3002c01v1Table  OBJECT-TYPE
			SYNTAX SEQUENCE OF Pdc3002c01v1Entry
			MAX-ACCESS not-accessible
			STATUS current
			DESCRIPTION
				"Module  PDC3002C01V1 Table"
			::= { pdc3002c01v1 1 }

		-- 1.3.6.1.4.1.10106.3.320501.1.1
		pdc3002c01v1Entry  OBJECT-TYPE
			SYNTAX Pdc3002c01v1Entry
			MAX-ACCESS not-accessible
			STATUS current
			DESCRIPTION
				"Module PDC3002C01V1 Entry"
			INDEX { pdc3002c01v1Index }
			::= { pdc3002c01v1Table 1 }

			Pdc3002c01v1Entry ::=
			SEQUENCE {
				pdc3002c01v1Index
				ModuleIndex,
				pdc3002c01v1BlackA
				Bit0Ccvs1Bb,
				pdc3002c01v1OutOnFailA
				Bit0Blk1Nos,
				pdc3002c01v1LinesA
				Bit06251525,
				pdc3002c01v1BlackB
				Bit0Ccvs1Bb,
				pdc3002c01v1OutOnFailB
				Bit0Blk1Nos,
				pdc3002c01v1LinesB
				Bit06251525,
				pdc3002c01v1UnlockA
				BitFail,
				pdc3002c01v1UnlockATrapEnable
				AlarmEnable,
				pdc3002c01v1UnlockB
				BitFail,
				pdc3002c01v1UnlockBTrapEnable
				AlarmEnable,
				pdc3002c01v1NoSigA
				BitFail,
				pdc3002c01v1NoSigATrapEnable
				AlarmEnable,
				pdc3002c01v1NoSigB
				BitFail,
				pdc3002c01v1NoSigBTrapEnable
				AlarmEnable,
				pdc3002c01v1VpsPresA
				Bit0No1Yes,
				pdc3002c01v1VpsPresB
				Bit0No1Yes,
				pdc3002c01v1SerialNo
				SerialNo
			 }

		-- 1.3.6.1.4.1.10106.3.101291.1.1.1
		pdc3002c01v1Index OBJECT-TYPE
			SYNTAX ModuleIndex
			MAX-ACCESS read-only
			STATUS current
			DESCRIPTION
				"Index of PDC3002C01V1 Table"
		::= { pdc3002c01v1Entry 1 }

		-- 1.3.6.1.4.1.10106.3.101291.1.1.3
		pdc3002c01v1BlackA OBJECT-TYPE
			SYNTAX Bit0Ccvs1Bb
			MAX-ACCESS read-write
			STATUS current
			DESCRIPTION
				"Allows selecting the signal at the output"
		::= { pdc3002c01v1Entry 3 }

		-- 1.3.6.1.4.1.10106.3.101291.1.1.5
		pdc3002c01v1OutOnFailA OBJECT-TYPE
			SYNTAX Bit0Blk1Nos
			MAX-ACCESS read-write
			STATUS current
			DESCRIPTION
				"Allows selecting the output signal if input signal fails"
		::= { pdc3002c01v1Entry 5 }

		-- 1.3.6.1.4.1.10106.3.101291.1.1.7
		pdc3002c01v1LinesA OBJECT-TYPE
			SYNTAX Bit06251525
			MAX-ACCESS read-write
			STATUS current
			DESCRIPTION
				"TV input signal line number"
		::= { pdc3002c01v1Entry 7 }

		-- 1.3.6.1.4.1.10106.3.101291.1.1.9
		pdc3002c01v1BlackB OBJECT-TYPE
			SYNTAX Bit0Ccvs1Bb
			MAX-ACCESS read-write
			STATUS current
			DESCRIPTION
				"Allows selecting the signal at the output"
		::= { pdc3002c01v1Entry 9 }

		-- 1.3.6.1.4.1.10106.3.101291.1.1.11
		pdc3002c01v1OutOnFailB OBJECT-TYPE
			SYNTAX Bit0Blk1Nos
			MAX-ACCESS read-write
			STATUS current
			DESCRIPTION
				"Allows selecting the output signal if input signal fails"
		::= { pdc3002c01v1Entry 11 }

		-- 1.3.6.1.4.1.10106.3.101291.1.1.13
		pdc3002c01v1LinesB OBJECT-TYPE
			SYNTAX Bit06251525
			MAX-ACCESS read-write
			STATUS current
			DESCRIPTION
				"TV input signal line number"
		::= { pdc3002c01v1Entry 13 }

		-- 1.3.6.1.4.1.10106.3.101291.1.1.15
		pdc3002c01v1UnlockA OBJECT-TYPE
			SYNTAX BitFail
			MAX-ACCESS read-only
			STATUS current
			DESCRIPTION
				"Indicates VCXO unlock fail"
		::= { pdc3002c01v1Entry 15 }

		-- 1.3.6.1.4.1.10106.3.101291.1.1.16
		pdc3002c01v1UnlockATrapEnable OBJECT-TYPE
			SYNTAX AlarmEnable
			MAX-ACCESS read-write
			STATUS current
			DESCRIPTION
				"Indicates VCXO unlock fail Trap Enable"
		::= { pdc3002c01v1Entry 16 }

		-- 1.3.6.1.4.1.10106.3.101291.1.1.17
		pdc3002c01v1UnlockB OBJECT-TYPE
			SYNTAX BitFail
			MAX-ACCESS read-only
			STATUS current
			DESCRIPTION
				"Indicates VCXO unlock fail"
		::= { pdc3002c01v1Entry 17 }

		-- 1.3.6.1.4.1.10106.3.101291.1.1.18
		pdc3002c01v1UnlockBTrapEnable OBJECT-TYPE
			SYNTAX AlarmEnable
			MAX-ACCESS read-write
			STATUS current
			DESCRIPTION
				"Indicates VCXO unlock fail Trap Enable"
		::= { pdc3002c01v1Entry 18 }

		-- 1.3.6.1.4.1.10106.3.101291.1.1.19
		pdc3002c01v1NoSigA OBJECT-TYPE
			SYNTAX BitFail
			MAX-ACCESS read-only
			STATUS current
			DESCRIPTION
				"Composite video signal status"
		::= { pdc3002c01v1Entry 19 }

		-- 1.3.6.1.4.1.10106.3.101291.1.1.20
		pdc3002c01v1NoSigATrapEnable OBJECT-TYPE
			SYNTAX AlarmEnable
			MAX-ACCESS read-write
			STATUS current
			DESCRIPTION
				"Composite video signal status Trap Enable"
		::= { pdc3002c01v1Entry 20 }

		-- 1.3.6.1.4.1.10106.3.101291.1.1.21
		pdc3002c01v1NoSigB OBJECT-TYPE
			SYNTAX BitFail
			MAX-ACCESS read-only
			STATUS current
			DESCRIPTION
				"Composite video signal status"
		::= { pdc3002c01v1Entry 21 }

		-- 1.3.6.1.4.1.10106.3.101291.1.1.22
		pdc3002c01v1NoSigBTrapEnable OBJECT-TYPE
			SYNTAX AlarmEnable
			MAX-ACCESS read-write
			STATUS current
			DESCRIPTION
				"Composite video signal status Trap Enable"
		::= { pdc3002c01v1Entry 22 }

		-- 1.3.6.1.4.1.10106.3.101291.1.1.23
		pdc3002c01v1VpsPresA OBJECT-TYPE
			SYNTAX Bit0No1Yes
			MAX-ACCESS read-only
			STATUS current
			DESCRIPTION
				"Indicates the presence of VPS signal"
		::= { pdc3002c01v1Entry 23 }

		-- 1.3.6.1.4.1.10106.3.101291.1.1.25
		pdc3002c01v1VpsPresB OBJECT-TYPE
			SYNTAX Bit0No1Yes
			MAX-ACCESS read-only
			STATUS current
			DESCRIPTION
				"Indicates the presence of VPS signal"
		::= { pdc3002c01v1Entry 25 }

		-- 1.3.6.1.4.1.10106.3.101291.1.1.27
		pdc3002c01v1SerialNo OBJECT-TYPE
			SYNTAX SerialNo
			MAX-ACCESS read-only
			STATUS current
			DESCRIPTION
				"Serial number"
		::= { pdc3002c01v1Entry 27 }

		-- 1.3.6.1.4.1.10106.3.324201
		vct3000c11v1 OBJECT IDENTIFIER ::= { albalaProducts 324201 }

		-- 1.3.6.1.4.1.10106.3.324201.1
		vct3000c11v1Table  OBJECT-TYPE
			SYNTAX SEQUENCE OF Vct3000c11v1Entry
			MAX-ACCESS not-accessible
			STATUS current
			DESCRIPTION
				"Module  VCT3000C11V1 Table"
			::= { vct3000c11v1 1 }

		-- 1.3.6.1.4.1.10106.3.324201.1.1
		vct3000c11v1Entry  OBJECT-TYPE
			SYNTAX Vct3000c11v1Entry
			MAX-ACCESS not-accessible
			STATUS current
			DESCRIPTION
				"Module VCT3000C11V1 Entry"
			INDEX { vct3000c11v1Index }
			::= { vct3000c11v1Table 1 }

			Vct3000c11v1Entry ::=
			SEQUENCE {
				vct3000c11v1Index
				ModuleIndex,
				vct3000c11v1Mode
				ChgOverMode2,
				vct3000c11v1ModeTrapEnable
				AlarmEnable,
				vct3000c11v1Buzzer
				BitMask,
				vct3000c11v1Input
				ChgOverInput1,
				vct3000c11v1InputTrapEnable
				AlarmEnable,
				vct3000c11v1InputChange
				Bit0No1Yes,
				vct3000c11v1RemoteEnable
				Bit0No1Yes,
				vct3000c11v1MainFail
				BitFail,
				vct3000c11v1MainFailTrapEnable
				AlarmEnable,
				vct3000c11v1ResFail
				BitFail,
				vct3000c11v1ResFailTrapEnable
				AlarmEnable,
				vct3000c11v1AuxFail
				BitFail,
				vct3000c11v1AuxFailTrapEnable
				AlarmEnable,
				vct3000c11v1Remote
				Bit0No1Yes,
				vct3000c11v1SerialNo
				SerialNo
			 }

		-- 1.3.6.1.4.1.10106.3.101291.1.1.1
		vct3000c11v1Index OBJECT-TYPE
			SYNTAX ModuleIndex
			MAX-ACCESS read-only
			STATUS current
			DESCRIPTION
				"Index of VCT3000C11V1 Table"
		::= { vct3000c11v1Entry 1 }

		-- 1.3.6.1.4.1.10106.3.101291.1.1.3
		vct3000c11v1Mode OBJECT-TYPE
			SYNTAX ChgOverMode2
			MAX-ACCESS read-write
			STATUS current
			DESCRIPTION
				"Allows selecting the switching mode"
		::= { vct3000c11v1Entry 3 }

		-- 1.3.6.1.4.1.10106.3.101291.1.1.4
		vct3000c11v1ModeTrapEnable OBJECT-TYPE
			SYNTAX AlarmEnable
			MAX-ACCESS read-write
			STATUS current
			DESCRIPTION
				"Allows selecting the switching mode Trap Enable"
		::= { vct3000c11v1Entry 4 }

		-- 1.3.6.1.4.1.10106.3.101291.1.1.5
		vct3000c11v1Buzzer OBJECT-TYPE
			SYNTAX BitMask
			MAX-ACCESS read-write
			STATUS current
			DESCRIPTION
				"Allows buzzer operation"
		::= { vct3000c11v1Entry 5 }

		-- 1.3.6.1.4.1.10106.3.101291.1.1.7
		vct3000c11v1Input OBJECT-TYPE
			SYNTAX ChgOverInput1
			MAX-ACCESS read-write
			STATUS current
			DESCRIPTION
				"Selected input"
		::= { vct3000c11v1Entry 7 }

		-- 1.3.6.1.4.1.10106.3.101291.1.1.8
		vct3000c11v1InputTrapEnable OBJECT-TYPE
			SYNTAX AlarmEnable
			MAX-ACCESS read-write
			STATUS current
			DESCRIPTION
				"Selected input Trap Enable"
		::= { vct3000c11v1Entry 8 }

		-- 1.3.6.1.4.1.10106.3.101291.1.1.9
		vct3000c11v1InputChange OBJECT-TYPE
			SYNTAX Bit0No1Yes
			MAX-ACCESS read-write
			STATUS current
			DESCRIPTION
				"Signals a change in selected input"
		::= { vct3000c11v1Entry 9 }

		-- 1.3.6.1.4.1.10106.3.101291.1.1.11
		vct3000c11v1RemoteEnable OBJECT-TYPE
			SYNTAX Bit0No1Yes
			MAX-ACCESS read-write
			STATUS current
			DESCRIPTION
				"Allows module to be GPI controlled"
		::= { vct3000c11v1Entry 11 }

		-- 1.3.6.1.4.1.10106.3.101291.1.1.13
		vct3000c11v1MainFail OBJECT-TYPE
			SYNTAX BitFail
			MAX-ACCESS read-only
			STATUS current
			DESCRIPTION
				"Main input status"
		::= { vct3000c11v1Entry 13 }

		-- 1.3.6.1.4.1.10106.3.101291.1.1.14
		vct3000c11v1MainFailTrapEnable OBJECT-TYPE
			SYNTAX AlarmEnable
			MAX-ACCESS read-write
			STATUS current
			DESCRIPTION
				"Main input status Trap Enable"
		::= { vct3000c11v1Entry 14 }

		-- 1.3.6.1.4.1.10106.3.101291.1.1.15
		vct3000c11v1ResFail OBJECT-TYPE
			SYNTAX BitFail
			MAX-ACCESS read-only
			STATUS current
			DESCRIPTION
				"Reserve input status"
		::= { vct3000c11v1Entry 15 }

		-- 1.3.6.1.4.1.10106.3.101291.1.1.16
		vct3000c11v1ResFailTrapEnable OBJECT-TYPE
			SYNTAX AlarmEnable
			MAX-ACCESS read-write
			STATUS current
			DESCRIPTION
				"Reserve input status Trap Enable"
		::= { vct3000c11v1Entry 16 }

		-- 1.3.6.1.4.1.10106.3.101291.1.1.17
		vct3000c11v1AuxFail OBJECT-TYPE
			SYNTAX BitFail
			MAX-ACCESS read-only
			STATUS current
			DESCRIPTION
				"Auxiliar input status"
		::= { vct3000c11v1Entry 17 }

		-- 1.3.6.1.4.1.10106.3.101291.1.1.18
		vct3000c11v1AuxFailTrapEnable OBJECT-TYPE
			SYNTAX AlarmEnable
			MAX-ACCESS read-write
			STATUS current
			DESCRIPTION
				"Auxiliar input status Trap Enable"
		::= { vct3000c11v1Entry 18 }

		-- 1.3.6.1.4.1.10106.3.101291.1.1.19
		vct3000c11v1Remote OBJECT-TYPE
			SYNTAX Bit0No1Yes
			MAX-ACCESS read-only
			STATUS current
			DESCRIPTION
				"Indicates when the module is GPI controlled"
		::= { vct3000c11v1Entry 19 }

		-- 1.3.6.1.4.1.10106.3.101291.1.1.21
		vct3000c11v1SerialNo OBJECT-TYPE
			SYNTAX SerialNo
			MAX-ACCESS read-only
			STATUS current
			DESCRIPTION
				"Serial number"
		::= { vct3000c11v1Entry 21 }

		-- 1.3.6.1.4.1.10106.3.324301
		vct3000c12v1 OBJECT IDENTIFIER ::= { albalaProducts 324301 }

		-- 1.3.6.1.4.1.10106.3.324301.1
		vct3000c12v1Table  OBJECT-TYPE
			SYNTAX SEQUENCE OF Vct3000c12v1Entry
			MAX-ACCESS not-accessible
			STATUS current
			DESCRIPTION
				"Module  VCT3000C12V1 Table"
			::= { vct3000c12v1 1 }

		-- 1.3.6.1.4.1.10106.3.324301.1.1
		vct3000c12v1Entry  OBJECT-TYPE
			SYNTAX Vct3000c12v1Entry
			MAX-ACCESS not-accessible
			STATUS current
			DESCRIPTION
				"Module VCT3000C12V1 Entry"
			INDEX { vct3000c12v1Index }
			::= { vct3000c12v1Table 1 }

			Vct3000c12v1Entry ::=
			SEQUENCE {
				vct3000c12v1Index
				ModuleIndex,
				vct3000c12v1Mode
				ChgOverMode2,
				vct3000c12v1ModeTrapEnable
				AlarmEnable,
				vct3000c12v1Buzzer
				BitMask,
				vct3000c12v1Input
				ChgOverInput1,
				vct3000c12v1InputTrapEnable
				AlarmEnable,
				vct3000c12v1InputChange
				Bit0No1Yes,
				vct3000c12v1RemoteEnable
				Bit0No1Yes,
				vct3000c12v1MainFail
				BitFail,
				vct3000c12v1MainFailTrapEnable
				AlarmEnable,
				vct3000c12v1ResFail
				BitFail,
				vct3000c12v1ResFailTrapEnable
				AlarmEnable,
				vct3000c12v1AuxFail
				BitFail,
				vct3000c12v1AuxFailTrapEnable
				AlarmEnable,
				vct3000c12v1Remote
				Bit0No1Yes,
				vct3000c12v1SerialNo
				SerialNo
			 }

		-- 1.3.6.1.4.1.10106.3.101291.1.1.1
		vct3000c12v1Index OBJECT-TYPE
			SYNTAX ModuleIndex
			MAX-ACCESS read-only
			STATUS current
			DESCRIPTION
				"Index of VCT3000C12V1 Table"
		::= { vct3000c12v1Entry 1 }

		-- 1.3.6.1.4.1.10106.3.101291.1.1.3
		vct3000c12v1Mode OBJECT-TYPE
			SYNTAX ChgOverMode2
			MAX-ACCESS read-write
			STATUS current
			DESCRIPTION
				"Allows selecting the switching mode"
		::= { vct3000c12v1Entry 3 }

		-- 1.3.6.1.4.1.10106.3.101291.1.1.4
		vct3000c12v1ModeTrapEnable OBJECT-TYPE
			SYNTAX AlarmEnable
			MAX-ACCESS read-write
			STATUS current
			DESCRIPTION
				"Allows selecting the switching mode Trap Enable"
		::= { vct3000c12v1Entry 4 }

		-- 1.3.6.1.4.1.10106.3.101291.1.1.5
		vct3000c12v1Buzzer OBJECT-TYPE
			SYNTAX BitMask
			MAX-ACCESS read-write
			STATUS current
			DESCRIPTION
				"Allows buzzer operation"
		::= { vct3000c12v1Entry 5 }

		-- 1.3.6.1.4.1.10106.3.101291.1.1.7
		vct3000c12v1Input OBJECT-TYPE
			SYNTAX ChgOverInput1
			MAX-ACCESS read-write
			STATUS current
			DESCRIPTION
				"Selected input"
		::= { vct3000c12v1Entry 7 }

		-- 1.3.6.1.4.1.10106.3.101291.1.1.8
		vct3000c12v1InputTrapEnable OBJECT-TYPE
			SYNTAX AlarmEnable
			MAX-ACCESS read-write
			STATUS current
			DESCRIPTION
				"Selected input Trap Enable"
		::= { vct3000c12v1Entry 8 }

		-- 1.3.6.1.4.1.10106.3.101291.1.1.9
		vct3000c12v1InputChange OBJECT-TYPE
			SYNTAX Bit0No1Yes
			MAX-ACCESS read-write
			STATUS current
			DESCRIPTION
				"Signals a change in selected input"
		::= { vct3000c12v1Entry 9 }

		-- 1.3.6.1.4.1.10106.3.101291.1.1.11
		vct3000c12v1RemoteEnable OBJECT-TYPE
			SYNTAX Bit0No1Yes
			MAX-ACCESS read-write
			STATUS current
			DESCRIPTION
				"Allows module to be GPI controlled"
		::= { vct3000c12v1Entry 11 }

		-- 1.3.6.1.4.1.10106.3.101291.1.1.13
		vct3000c12v1MainFail OBJECT-TYPE
			SYNTAX BitFail
			MAX-ACCESS read-only
			STATUS current
			DESCRIPTION
				"Main input status"
		::= { vct3000c12v1Entry 13 }

		-- 1.3.6.1.4.1.10106.3.101291.1.1.14
		vct3000c12v1MainFailTrapEnable OBJECT-TYPE
			SYNTAX AlarmEnable
			MAX-ACCESS read-write
			STATUS current
			DESCRIPTION
				"Main input status Trap Enable"
		::= { vct3000c12v1Entry 14 }

		-- 1.3.6.1.4.1.10106.3.101291.1.1.15
		vct3000c12v1ResFail OBJECT-TYPE
			SYNTAX BitFail
			MAX-ACCESS read-only
			STATUS current
			DESCRIPTION
				"Reserve input status"
		::= { vct3000c12v1Entry 15 }

		-- 1.3.6.1.4.1.10106.3.101291.1.1.16
		vct3000c12v1ResFailTrapEnable OBJECT-TYPE
			SYNTAX AlarmEnable
			MAX-ACCESS read-write
			STATUS current
			DESCRIPTION
				"Reserve input status Trap Enable"
		::= { vct3000c12v1Entry 16 }

		-- 1.3.6.1.4.1.10106.3.101291.1.1.17
		vct3000c12v1AuxFail OBJECT-TYPE
			SYNTAX BitFail
			MAX-ACCESS read-only
			STATUS current
			DESCRIPTION
				"Auxiliar input status"
		::= { vct3000c12v1Entry 17 }

		-- 1.3.6.1.4.1.10106.3.101291.1.1.18
		vct3000c12v1AuxFailTrapEnable OBJECT-TYPE
			SYNTAX AlarmEnable
			MAX-ACCESS read-write
			STATUS current
			DESCRIPTION
				"Auxiliar input status Trap Enable"
		::= { vct3000c12v1Entry 18 }

		-- 1.3.6.1.4.1.10106.3.101291.1.1.19
		vct3000c12v1Remote OBJECT-TYPE
			SYNTAX Bit0No1Yes
			MAX-ACCESS read-only
			STATUS current
			DESCRIPTION
				"Indicates when the module is GPI controlled"
		::= { vct3000c12v1Entry 19 }

		-- 1.3.6.1.4.1.10106.3.101291.1.1.21
		vct3000c12v1SerialNo OBJECT-TYPE
			SYNTAX SerialNo
			MAX-ACCESS read-only
			STATUS current
			DESCRIPTION
				"Serial number"
		::= { vct3000c12v1Entry 21 }

		-- 1.3.6.1.4.1.10106.3.324401
		vct3000c14v1 OBJECT IDENTIFIER ::= { albalaProducts 324401 }

		-- 1.3.6.1.4.1.10106.3.324401.1
		vct3000c14v1Table  OBJECT-TYPE
			SYNTAX SEQUENCE OF Vct3000c14v1Entry
			MAX-ACCESS not-accessible
			STATUS current
			DESCRIPTION
				"Module  VCT3000C14V1 Table"
			::= { vct3000c14v1 1 }

		-- 1.3.6.1.4.1.10106.3.324401.1.1
		vct3000c14v1Entry  OBJECT-TYPE
			SYNTAX Vct3000c14v1Entry
			MAX-ACCESS not-accessible
			STATUS current
			DESCRIPTION
				"Module VCT3000C14V1 Entry"
			INDEX { vct3000c14v1Index }
			::= { vct3000c14v1Table 1 }

			Vct3000c14v1Entry ::=
			SEQUENCE {
				vct3000c14v1Index
				ModuleIndex,
				vct3000c14v1Mode
				ChgOverMode2,
				vct3000c14v1ModeTrapEnable
				AlarmEnable,
				vct3000c14v1Buzzer
				BitMask,
				vct3000c14v1Input
				ChgOverInput1,
				vct3000c14v1InputTrapEnable
				AlarmEnable,
				vct3000c14v1InputChange
				Bit0No1Yes,
				vct3000c14v1RemoteEnable
				Bit0No1Yes,
				vct3000c14v1MainFail
				BitFail,
				vct3000c14v1MainFailTrapEnable
				AlarmEnable,
				vct3000c14v1ResFail
				BitFail,
				vct3000c14v1ResFailTrapEnable
				AlarmEnable,
				vct3000c14v1AuxFail
				BitFail,
				vct3000c14v1AuxFailTrapEnable
				AlarmEnable,
				vct3000c14v1Remote
				Bit0No1Yes,
				vct3000c14v1SerialNo
				SerialNo
			 }

		-- 1.3.6.1.4.1.10106.3.101291.1.1.1
		vct3000c14v1Index OBJECT-TYPE
			SYNTAX ModuleIndex
			MAX-ACCESS read-only
			STATUS current
			DESCRIPTION
				"Index of VCT3000C14V1 Table"
		::= { vct3000c14v1Entry 1 }

		-- 1.3.6.1.4.1.10106.3.101291.1.1.3
		vct3000c14v1Mode OBJECT-TYPE
			SYNTAX ChgOverMode2
			MAX-ACCESS read-write
			STATUS current
			DESCRIPTION
				"Allows selecting the switching mode"
		::= { vct3000c14v1Entry 3 }

		-- 1.3.6.1.4.1.10106.3.101291.1.1.4
		vct3000c14v1ModeTrapEnable OBJECT-TYPE
			SYNTAX AlarmEnable
			MAX-ACCESS read-write
			STATUS current
			DESCRIPTION
				"Allows selecting the switching mode Trap Enable"
		::= { vct3000c14v1Entry 4 }

		-- 1.3.6.1.4.1.10106.3.101291.1.1.5
		vct3000c14v1Buzzer OBJECT-TYPE
			SYNTAX BitMask
			MAX-ACCESS read-write
			STATUS current
			DESCRIPTION
				"Allows buzzer operation"
		::= { vct3000c14v1Entry 5 }

		-- 1.3.6.1.4.1.10106.3.101291.1.1.7
		vct3000c14v1Input OBJECT-TYPE
			SYNTAX ChgOverInput1
			MAX-ACCESS read-write
			STATUS current
			DESCRIPTION
				"Selected input"
		::= { vct3000c14v1Entry 7 }

		-- 1.3.6.1.4.1.10106.3.101291.1.1.8
		vct3000c14v1InputTrapEnable OBJECT-TYPE
			SYNTAX AlarmEnable
			MAX-ACCESS read-write
			STATUS current
			DESCRIPTION
				"Selected input Trap Enable"
		::= { vct3000c14v1Entry 8 }

		-- 1.3.6.1.4.1.10106.3.101291.1.1.9
		vct3000c14v1InputChange OBJECT-TYPE
			SYNTAX Bit0No1Yes
			MAX-ACCESS read-write
			STATUS current
			DESCRIPTION
				"Signals a change in selected input"
		::= { vct3000c14v1Entry 9 }

		-- 1.3.6.1.4.1.10106.3.101291.1.1.11
		vct3000c14v1RemoteEnable OBJECT-TYPE
			SYNTAX Bit0No1Yes
			MAX-ACCESS read-write
			STATUS current
			DESCRIPTION
				"Allows module to be GPI controlled"
		::= { vct3000c14v1Entry 11 }

		-- 1.3.6.1.4.1.10106.3.101291.1.1.13
		vct3000c14v1MainFail OBJECT-TYPE
			SYNTAX BitFail
			MAX-ACCESS read-only
			STATUS current
			DESCRIPTION
				"Main input status"
		::= { vct3000c14v1Entry 13 }

		-- 1.3.6.1.4.1.10106.3.101291.1.1.14
		vct3000c14v1MainFailTrapEnable OBJECT-TYPE
			SYNTAX AlarmEnable
			MAX-ACCESS read-write
			STATUS current
			DESCRIPTION
				"Main input status Trap Enable"
		::= { vct3000c14v1Entry 14 }

		-- 1.3.6.1.4.1.10106.3.101291.1.1.15
		vct3000c14v1ResFail OBJECT-TYPE
			SYNTAX BitFail
			MAX-ACCESS read-only
			STATUS current
			DESCRIPTION
				"Reserve input status"
		::= { vct3000c14v1Entry 15 }

		-- 1.3.6.1.4.1.10106.3.101291.1.1.16
		vct3000c14v1ResFailTrapEnable OBJECT-TYPE
			SYNTAX AlarmEnable
			MAX-ACCESS read-write
			STATUS current
			DESCRIPTION
				"Reserve input status Trap Enable"
		::= { vct3000c14v1Entry 16 }

		-- 1.3.6.1.4.1.10106.3.101291.1.1.17
		vct3000c14v1AuxFail OBJECT-TYPE
			SYNTAX BitFail
			MAX-ACCESS read-only
			STATUS current
			DESCRIPTION
				"Auxiliar input status"
		::= { vct3000c14v1Entry 17 }

		-- 1.3.6.1.4.1.10106.3.101291.1.1.18
		vct3000c14v1AuxFailTrapEnable OBJECT-TYPE
			SYNTAX AlarmEnable
			MAX-ACCESS read-write
			STATUS current
			DESCRIPTION
				"Auxiliar input status Trap Enable"
		::= { vct3000c14v1Entry 18 }

		-- 1.3.6.1.4.1.10106.3.101291.1.1.19
		vct3000c14v1Remote OBJECT-TYPE
			SYNTAX Bit0No1Yes
			MAX-ACCESS read-only
			STATUS current
			DESCRIPTION
				"Indicates when the module is GPI controlled"
		::= { vct3000c14v1Entry 19 }

		-- 1.3.6.1.4.1.10106.3.101291.1.1.21
		vct3000c14v1SerialNo OBJECT-TYPE
			SYNTAX SerialNo
			MAX-ACCESS read-only
			STATUS current
			DESCRIPTION
				"Serial number"
		::= { vct3000c14v1Entry 21 }

		-- 1.3.6.1.4.1.10106.3.324501
		vct3000c15v1 OBJECT IDENTIFIER ::= { albalaProducts 324501 }

		-- 1.3.6.1.4.1.10106.3.324501.1
		vct3000c15v1Table  OBJECT-TYPE
			SYNTAX SEQUENCE OF Vct3000c15v1Entry
			MAX-ACCESS not-accessible
			STATUS current
			DESCRIPTION
				"Module  VCT3000C15V1 Table"
			::= { vct3000c15v1 1 }

		-- 1.3.6.1.4.1.10106.3.324501.1.1
		vct3000c15v1Entry  OBJECT-TYPE
			SYNTAX Vct3000c15v1Entry
			MAX-ACCESS not-accessible
			STATUS current
			DESCRIPTION
				"Module VCT3000C15V1 Entry"
			INDEX { vct3000c15v1Index }
			::= { vct3000c15v1Table 1 }

			Vct3000c15v1Entry ::=
			SEQUENCE {
				vct3000c15v1Index
				ModuleIndex,
				vct3000c15v1Mode
				ChgOverMode2,
				vct3000c15v1ModeTrapEnable
				AlarmEnable,
				vct3000c15v1Buzzer
				BitMask,
				vct3000c15v1Input
				ChgOverInput1,
				vct3000c15v1InputTrapEnable
				AlarmEnable,
				vct3000c15v1InputChange
				Bit0No1Yes,
				vct3000c15v1RemoteEnable
				Bit0No1Yes,
				vct3000c15v1MainFail
				BitFail,
				vct3000c15v1MainFailTrapEnable
				AlarmEnable,
				vct3000c15v1ResFail
				BitFail,
				vct3000c15v1ResFailTrapEnable
				AlarmEnable,
				vct3000c15v1AuxFail
				BitFail,
				vct3000c15v1AuxFailTrapEnable
				AlarmEnable,
				vct3000c15v1Remote
				Bit0No1Yes,
				vct3000c15v1SerialNo
				SerialNo
			 }

		-- 1.3.6.1.4.1.10106.3.101291.1.1.1
		vct3000c15v1Index OBJECT-TYPE
			SYNTAX ModuleIndex
			MAX-ACCESS read-only
			STATUS current
			DESCRIPTION
				"Index of VCT3000C15V1 Table"
		::= { vct3000c15v1Entry 1 }

		-- 1.3.6.1.4.1.10106.3.101291.1.1.3
		vct3000c15v1Mode OBJECT-TYPE
			SYNTAX ChgOverMode2
			MAX-ACCESS read-write
			STATUS current
			DESCRIPTION
				"Allows selecting the switching mode"
		::= { vct3000c15v1Entry 3 }

		-- 1.3.6.1.4.1.10106.3.101291.1.1.4
		vct3000c15v1ModeTrapEnable OBJECT-TYPE
			SYNTAX AlarmEnable
			MAX-ACCESS read-write
			STATUS current
			DESCRIPTION
				"Allows selecting the switching mode Trap Enable"
		::= { vct3000c15v1Entry 4 }

		-- 1.3.6.1.4.1.10106.3.101291.1.1.5
		vct3000c15v1Buzzer OBJECT-TYPE
			SYNTAX BitMask
			MAX-ACCESS read-write
			STATUS current
			DESCRIPTION
				"Allows buzzer operation"
		::= { vct3000c15v1Entry 5 }

		-- 1.3.6.1.4.1.10106.3.101291.1.1.7
		vct3000c15v1Input OBJECT-TYPE
			SYNTAX ChgOverInput1
			MAX-ACCESS read-write
			STATUS current
			DESCRIPTION
				"Selected input"
		::= { vct3000c15v1Entry 7 }

		-- 1.3.6.1.4.1.10106.3.101291.1.1.8
		vct3000c15v1InputTrapEnable OBJECT-TYPE
			SYNTAX AlarmEnable
			MAX-ACCESS read-write
			STATUS current
			DESCRIPTION
				"Selected input Trap Enable"
		::= { vct3000c15v1Entry 8 }

		-- 1.3.6.1.4.1.10106.3.101291.1.1.9
		vct3000c15v1InputChange OBJECT-TYPE
			SYNTAX Bit0No1Yes
			MAX-ACCESS read-write
			STATUS current
			DESCRIPTION
				"Signals a change in selected input"
		::= { vct3000c15v1Entry 9 }

		-- 1.3.6.1.4.1.10106.3.101291.1.1.11
		vct3000c15v1RemoteEnable OBJECT-TYPE
			SYNTAX Bit0No1Yes
			MAX-ACCESS read-write
			STATUS current
			DESCRIPTION
				"Allows module to be GPI controlled"
		::= { vct3000c15v1Entry 11 }

		-- 1.3.6.1.4.1.10106.3.101291.1.1.13
		vct3000c15v1MainFail OBJECT-TYPE
			SYNTAX BitFail
			MAX-ACCESS read-only
			STATUS current
			DESCRIPTION
				"Main input status"
		::= { vct3000c15v1Entry 13 }

		-- 1.3.6.1.4.1.10106.3.101291.1.1.14
		vct3000c15v1MainFailTrapEnable OBJECT-TYPE
			SYNTAX AlarmEnable
			MAX-ACCESS read-write
			STATUS current
			DESCRIPTION
				"Main input status Trap Enable"
		::= { vct3000c15v1Entry 14 }

		-- 1.3.6.1.4.1.10106.3.101291.1.1.15
		vct3000c15v1ResFail OBJECT-TYPE
			SYNTAX BitFail
			MAX-ACCESS read-only
			STATUS current
			DESCRIPTION
				"Reserve input status"
		::= { vct3000c15v1Entry 15 }

		-- 1.3.6.1.4.1.10106.3.101291.1.1.16
		vct3000c15v1ResFailTrapEnable OBJECT-TYPE
			SYNTAX AlarmEnable
			MAX-ACCESS read-write
			STATUS current
			DESCRIPTION
				"Reserve input status Trap Enable"
		::= { vct3000c15v1Entry 16 }

		-- 1.3.6.1.4.1.10106.3.101291.1.1.17
		vct3000c15v1AuxFail OBJECT-TYPE
			SYNTAX BitFail
			MAX-ACCESS read-only
			STATUS current
			DESCRIPTION
				"Auxiliar input status"
		::= { vct3000c15v1Entry 17 }

		-- 1.3.6.1.4.1.10106.3.101291.1.1.18
		vct3000c15v1AuxFailTrapEnable OBJECT-TYPE
			SYNTAX AlarmEnable
			MAX-ACCESS read-write
			STATUS current
			DESCRIPTION
				"Auxiliar input status Trap Enable"
		::= { vct3000c15v1Entry 18 }

		-- 1.3.6.1.4.1.10106.3.101291.1.1.19
		vct3000c15v1Remote OBJECT-TYPE
			SYNTAX Bit0No1Yes
			MAX-ACCESS read-only
			STATUS current
			DESCRIPTION
				"Indicates when the module is GPI controlled"
		::= { vct3000c15v1Entry 19 }

		-- 1.3.6.1.4.1.10106.3.101291.1.1.21
		vct3000c15v1SerialNo OBJECT-TYPE
			SYNTAX SerialNo
			MAX-ACCESS read-only
			STATUS current
			DESCRIPTION
				"Serial number"
		::= { vct3000c15v1Entry 21 }

		-- 1.3.6.1.4.1.10106.3.327001
		vtl3000c01v1 OBJECT IDENTIFIER ::= { albalaProducts 327001 }

		-- 1.3.6.1.4.1.10106.3.327001.1
		vtl3000c01v1Table  OBJECT-TYPE
			SYNTAX SEQUENCE OF Vtl3000c01v1Entry
			MAX-ACCESS not-accessible
			STATUS current
			DESCRIPTION
				"Module  VTL3000C01V1 Table"
			::= { vtl3000c01v1 1 }

		-- 1.3.6.1.4.1.10106.3.327001.1.1
		vtl3000c01v1Entry  OBJECT-TYPE
			SYNTAX Vtl3000c01v1Entry
			MAX-ACCESS not-accessible
			STATUS current
			DESCRIPTION
				"Module VTL3000C01V1 Entry"
			INDEX { vtl3000c01v1Index }
			::= { vtl3000c01v1Table 1 }

			Vtl3000c01v1Entry ::=
			SEQUENCE {
				vtl3000c01v1Index
				ModuleIndex,
				vtl3000c01v1VitcRdLine
				VideoLine,
				vtl3000c01v1NoSignal
				BitFail,
				vtl3000c01v1NoSignalTrapEnable
				AlarmEnable,
				vtl3000c01v1VitcOk
				Bit0No1Yes,
				vtl3000c01v1VitcHour
				TimeH1,
				vtl3000c01v1VitcMin
				TimeM1,
				vtl3000c01v1VitcSec
				TimeS1,
				vtl3000c01v1VitcFrame
				Uint8,
				vtl3000c01v1StatReset
				BitMask,
				vtl3000c01v1DupTc
				Uint8,
				vtl3000c01v1DupTcTrapEnable
				AlarmEnable,
				vtl3000c01v1LostTc
				Uint8,
				vtl3000c01v1LostTcTrapEnable
				AlarmEnable,
				vtl3000c01v1NoTcFrame
				Uint8,
				vtl3000c01v1NoTcFrameTrapEnable
				AlarmEnable,
				vtl3000c01v1StatMinutes
				TimeX1Min
			 }

		-- 1.3.6.1.4.1.10106.3.101291.1.1.1
		vtl3000c01v1Index OBJECT-TYPE
			SYNTAX ModuleIndex
			MAX-ACCESS read-only
			STATUS current
			DESCRIPTION
				"Index of VTL3000C01V1 Table"
		::= { vtl3000c01v1Entry 1 }

		-- 1.3.6.1.4.1.10106.3.101291.1.1.3
		vtl3000c01v1VitcRdLine OBJECT-TYPE
			SYNTAX VideoLine
			MAX-ACCESS read-write
			STATUS current
			DESCRIPTION
				"Allows selecting the VBI line that contains the VITC information"
		::= { vtl3000c01v1Entry 3 }

		-- 1.3.6.1.4.1.10106.3.101291.1.1.5
		vtl3000c01v1NoSignal OBJECT-TYPE
			SYNTAX BitFail
			MAX-ACCESS read-only
			STATUS current
			DESCRIPTION
				"SDI input signal status"
		::= { vtl3000c01v1Entry 5 }

		-- 1.3.6.1.4.1.10106.3.101291.1.1.6
		vtl3000c01v1NoSignalTrapEnable OBJECT-TYPE
			SYNTAX AlarmEnable
			MAX-ACCESS read-write
			STATUS current
			DESCRIPTION
				"SDI input signal status Trap Enable"
		::= { vtl3000c01v1Entry 6 }

		-- 1.3.6.1.4.1.10106.3.101291.1.1.7
		vtl3000c01v1VitcOk OBJECT-TYPE
			SYNTAX Bit0No1Yes
			MAX-ACCESS read-only
			STATUS current
			DESCRIPTION
				"The VITC data have been correcty decoded"
		::= { vtl3000c01v1Entry 7 }

		-- 1.3.6.1.4.1.10106.3.101291.1.1.9
		vtl3000c01v1VitcHour OBJECT-TYPE
			SYNTAX TimeH1
			MAX-ACCESS read-only
			STATUS current
			DESCRIPTION
				"Hour read from VITC"
		::= { vtl3000c01v1Entry 9 }

		-- 1.3.6.1.4.1.10106.3.101291.1.1.11
		vtl3000c01v1VitcMin OBJECT-TYPE
			SYNTAX TimeM1
			MAX-ACCESS read-only
			STATUS current
			DESCRIPTION
				"Minute read from VITC"
		::= { vtl3000c01v1Entry 11 }

		-- 1.3.6.1.4.1.10106.3.101291.1.1.13
		vtl3000c01v1VitcSec OBJECT-TYPE
			SYNTAX TimeS1
			MAX-ACCESS read-only
			STATUS current
			DESCRIPTION
				"Second read from VITC"
		::= { vtl3000c01v1Entry 13 }

		-- 1.3.6.1.4.1.10106.3.101291.1.1.15
		vtl3000c01v1VitcFrame OBJECT-TYPE
			SYNTAX Uint8
			MAX-ACCESS read-only
			STATUS current
			DESCRIPTION
				"Frame read from VITC"
		::= { vtl3000c01v1Entry 15 }

		-- 1.3.6.1.4.1.10106.3.101291.1.1.17
		vtl3000c01v1StatReset OBJECT-TYPE
			SYNTAX BitMask
			MAX-ACCESS read-write
			STATUS current
			DESCRIPTION
				"Counters reset"
		::= { vtl3000c01v1Entry 17 }

		-- 1.3.6.1.4.1.10106.3.101291.1.1.19
		vtl3000c01v1DupTc OBJECT-TYPE
			SYNTAX Uint8
			MAX-ACCESS read-only
			STATUS current
			DESCRIPTION
				"Duplicated time code"
		::= { vtl3000c01v1Entry 19 }

		-- 1.3.6.1.4.1.10106.3.101291.1.1.20
		vtl3000c01v1DupTcTrapEnable OBJECT-TYPE
			SYNTAX AlarmEnable
			MAX-ACCESS read-write
			STATUS current
			DESCRIPTION
				"Duplicated time code Trap Enable"
		::= { vtl3000c01v1Entry 20 }

		-- 1.3.6.1.4.1.10106.3.101291.1.1.21
		vtl3000c01v1LostTc OBJECT-TYPE
			SYNTAX Uint8
			MAX-ACCESS read-only
			STATUS current
			DESCRIPTION
				"Discontinuous time code"
		::= { vtl3000c01v1Entry 21 }

		-- 1.3.6.1.4.1.10106.3.101291.1.1.22
		vtl3000c01v1LostTcTrapEnable OBJECT-TYPE
			SYNTAX AlarmEnable
			MAX-ACCESS read-write
			STATUS current
			DESCRIPTION
				"Discontinuous time code Trap Enable"
		::= { vtl3000c01v1Entry 22 }

		-- 1.3.6.1.4.1.10106.3.101291.1.1.23
		vtl3000c01v1NoTcFrame OBJECT-TYPE
			SYNTAX Uint8
			MAX-ACCESS read-only
			STATUS current
			DESCRIPTION
				"Missing time code"
		::= { vtl3000c01v1Entry 23 }

		-- 1.3.6.1.4.1.10106.3.101291.1.1.24
		vtl3000c01v1NoTcFrameTrapEnable OBJECT-TYPE
			SYNTAX AlarmEnable
			MAX-ACCESS read-write
			STATUS current
			DESCRIPTION
				"Missing time code Trap Enable"
		::= { vtl3000c01v1Entry 24 }

		-- 1.3.6.1.4.1.10106.3.101291.1.1.25
		vtl3000c01v1StatMinutes OBJECT-TYPE
			SYNTAX TimeX1Min
			MAX-ACCESS read-only
			STATUS current
			DESCRIPTION
				"Minutes since reset"
		::= { vtl3000c01v1Entry 25 }

		-- 1.3.6.1.4.1.10106.3.328401
		tle3001c01v1 OBJECT IDENTIFIER ::= { albalaProducts 328401 }

		-- 1.3.6.1.4.1.10106.3.328401.1
		tle3001c01v1Table  OBJECT-TYPE
			SYNTAX SEQUENCE OF Tle3001c01v1Entry
			MAX-ACCESS not-accessible
			STATUS current
			DESCRIPTION
				"Module  TLE3001C01V1 Table"
			::= { tle3001c01v1 1 }

		-- 1.3.6.1.4.1.10106.3.328401.1.1
		tle3001c01v1Entry  OBJECT-TYPE
			SYNTAX Tle3001c01v1Entry
			MAX-ACCESS not-accessible
			STATUS current
			DESCRIPTION
				"Module TLE3001C01V1 Entry"
			INDEX { tle3001c01v1Index }
			::= { tle3001c01v1Table 1 }

			Tle3001c01v1Entry ::=
			SEQUENCE {
				tle3001c01v1Index
				ModuleIndex,
				tle3001c01v1Serial485232
				Bit04851232,
				tle3001c01v1ConsoleEna
				Bit0No1Yes,
				tle3001c01v1Gpo1
				Bit0Ina1Act,
				tle3001c01v1Gpo2
				Bit0Ina1Act,
				tle3001c01v1Gpo3
				Bit0Ina1Act,
				tle3001c01v1Gpo4
				Bit0Ina1Act,
				tle3001c01v1InvertGpi1Pol
				Bit0No1Yes,
				tle3001c01v1InvertGpi2Pol
				Bit0No1Yes,
				tle3001c01v1InvertGpi3Pol
				Bit0No1Yes,
				tle3001c01v1InvertGpi4Pol
				Bit0No1Yes,
				tle3001c01v1InvertGpo1Pol
				Bit0No1Yes,
				tle3001c01v1InvertGpo2Pol
				Bit0No1Yes,
				tle3001c01v1InvertGpo3Pol
				Bit0No1Yes,
				tle3001c01v1InvertGpo4Pol
				Bit0No1Yes,
				tle3001c01v1Gpi1
				Bit0Ina1Act,
				tle3001c01v1Gpi1TrapEnable
				AlarmEnable,
				tle3001c01v1Gpi2
				Bit0Ina1Act,
				tle3001c01v1Gpi2TrapEnable
				AlarmEnable,
				tle3001c01v1Gpi3
				Bit0Ina1Act,
				tle3001c01v1Gpi3TrapEnable
				AlarmEnable,
				tle3001c01v1Gpi4
				Bit0Ina1Act,
				tle3001c01v1Gpi4TrapEnable
				AlarmEnable,
				tle3001c01v1RedBoard
				Bit0No1Yes,
				tle3001c01v1RedBoardTrapEnable
				AlarmEnable,
				tle3001c01v1EthLink
				Bit0No1Yes,
				tle3001c01v1EthLinkTrapEnable
				AlarmEnable,
				tle3001c01v1EthRedAct
				Bit0No1Yes,
				tle3001c01v1EthRedActTrapEnable
				AlarmEnable,
				tle3001c01v1App1Ena
				Bit0No1Yes,
				tle3001c01v1App2Ena
				Bit0No1Yes,
				tle3001c01v1App3Ena
				Bit0No1Yes,
				tle3001c01v1App4Ena
				Bit0No1Yes,
				tle3001c01v1App5Ena
				Bit0No1Yes,
				tle3001c01v1App6Ena
				Bit0No1Yes,
				tle3001c01v1App7Ena
				Bit0No1Yes,
				tle3001c01v1App8Ena
				Bit0No1Yes,
				tle3001c01v1App9Ena
				Bit0No1Yes,
				tle3001c01v1App10Ena
				Bit0No1Yes,
				tle3001c01v1App11Ena
				Bit0No1Yes,
				tle3001c01v1App12Ena
				Bit0No1Yes,
				tle3001c01v1App13Ena
				Bit0No1Yes,
				tle3001c01v1App14Ena
				Bit0No1Yes,
				tle3001c01v1App15Ena
				Bit0No1Yes,
				tle3001c01v1App16Ena
				Bit0No1Yes,
				tle3001c01v1SerialNo
				SerialNo
			 }

		-- 1.3.6.1.4.1.10106.3.101291.1.1.1
		tle3001c01v1Index OBJECT-TYPE
			SYNTAX ModuleIndex
			MAX-ACCESS read-only
			STATUS current
			DESCRIPTION
				"Index of TLE3001C01V1 Table"
		::= { tle3001c01v1Entry 1 }

		-- 1.3.6.1.4.1.10106.3.101291.1.1.3
		tle3001c01v1Serial485232 OBJECT-TYPE
			SYNTAX Bit04851232
			MAX-ACCESS read-write
			STATUS current
			DESCRIPTION
				"Allows selecting the serial port levels"
		::= { tle3001c01v1Entry 3 }

		-- 1.3.6.1.4.1.10106.3.101291.1.1.5
		tle3001c01v1ConsoleEna OBJECT-TYPE
			SYNTAX Bit0No1Yes
			MAX-ACCESS read-write
			STATUS current
			DESCRIPTION
				"Allows using the serial port for the consola"
		::= { tle3001c01v1Entry 5 }

		-- 1.3.6.1.4.1.10106.3.101291.1.1.7
		tle3001c01v1Gpo1 OBJECT-TYPE
			SYNTAX Bit0Ina1Act
			MAX-ACCESS read-write
			STATUS current
			DESCRIPTION
				"Allows control of GPO1"
		::= { tle3001c01v1Entry 7 }

		-- 1.3.6.1.4.1.10106.3.101291.1.1.9
		tle3001c01v1Gpo2 OBJECT-TYPE
			SYNTAX Bit0Ina1Act
			MAX-ACCESS read-write
			STATUS current
			DESCRIPTION
				"Allows control of GPO2"
		::= { tle3001c01v1Entry 9 }

		-- 1.3.6.1.4.1.10106.3.101291.1.1.11
		tle3001c01v1Gpo3 OBJECT-TYPE
			SYNTAX Bit0Ina1Act
			MAX-ACCESS read-write
			STATUS current
			DESCRIPTION
				"Allows control of GPO3"
		::= { tle3001c01v1Entry 11 }

		-- 1.3.6.1.4.1.10106.3.101291.1.1.13
		tle3001c01v1Gpo4 OBJECT-TYPE
			SYNTAX Bit0Ina1Act
			MAX-ACCESS read-write
			STATUS current
			DESCRIPTION
				"Allows control of GPO4"
		::= { tle3001c01v1Entry 13 }

		-- 1.3.6.1.4.1.10106.3.101291.1.1.15
		tle3001c01v1InvertGpi1Pol OBJECT-TYPE
			SYNTAX Bit0No1Yes
			MAX-ACCESS read-write
			STATUS current
			DESCRIPTION
				"Changes GPI1 polarity to normally closed"
		::= { tle3001c01v1Entry 15 }

		-- 1.3.6.1.4.1.10106.3.101291.1.1.17
		tle3001c01v1InvertGpi2Pol OBJECT-TYPE
			SYNTAX Bit0No1Yes
			MAX-ACCESS read-write
			STATUS current
			DESCRIPTION
				"Changes GPI2 polarity to normally closed"
		::= { tle3001c01v1Entry 17 }

		-- 1.3.6.1.4.1.10106.3.101291.1.1.19
		tle3001c01v1InvertGpi3Pol OBJECT-TYPE
			SYNTAX Bit0No1Yes
			MAX-ACCESS read-write
			STATUS current
			DESCRIPTION
				"Changes GPI3 polarity to normally closed"
		::= { tle3001c01v1Entry 19 }

		-- 1.3.6.1.4.1.10106.3.101291.1.1.21
		tle3001c01v1InvertGpi4Pol OBJECT-TYPE
			SYNTAX Bit0No1Yes
			MAX-ACCESS read-write
			STATUS current
			DESCRIPTION
				"Changes GPI4 polarity to normally closed"
		::= { tle3001c01v1Entry 21 }

		-- 1.3.6.1.4.1.10106.3.101291.1.1.23
		tle3001c01v1InvertGpo1Pol OBJECT-TYPE
			SYNTAX Bit0No1Yes
			MAX-ACCESS read-write
			STATUS current
			DESCRIPTION
				"Allows inverting GPO1 polarity"
		::= { tle3001c01v1Entry 23 }

		-- 1.3.6.1.4.1.10106.3.101291.1.1.25
		tle3001c01v1InvertGpo2Pol OBJECT-TYPE
			SYNTAX Bit0No1Yes
			MAX-ACCESS read-write
			STATUS current
			DESCRIPTION
				"Allows inverting GPO2 polarity"
		::= { tle3001c01v1Entry 25 }

		-- 1.3.6.1.4.1.10106.3.101291.1.1.27
		tle3001c01v1InvertGpo3Pol OBJECT-TYPE
			SYNTAX Bit0No1Yes
			MAX-ACCESS read-write
			STATUS current
			DESCRIPTION
				"Allows inverting GPO3 polarity"
		::= { tle3001c01v1Entry 27 }

		-- 1.3.6.1.4.1.10106.3.101291.1.1.29
		tle3001c01v1InvertGpo4Pol OBJECT-TYPE
			SYNTAX Bit0No1Yes
			MAX-ACCESS read-write
			STATUS current
			DESCRIPTION
				"Allows inverting GPO4 polarity"
		::= { tle3001c01v1Entry 29 }

		-- 1.3.6.1.4.1.10106.3.101291.1.1.31
		tle3001c01v1Gpi1 OBJECT-TYPE
			SYNTAX Bit0Ina1Act
			MAX-ACCESS read-only
			STATUS current
			DESCRIPTION
				"GPI1 status"
		::= { tle3001c01v1Entry 31 }

		-- 1.3.6.1.4.1.10106.3.101291.1.1.32
		tle3001c01v1Gpi1TrapEnable OBJECT-TYPE
			SYNTAX AlarmEnable
			MAX-ACCESS read-write
			STATUS current
			DESCRIPTION
				"GPI1 status Trap Enable"
		::= { tle3001c01v1Entry 32 }

		-- 1.3.6.1.4.1.10106.3.101291.1.1.33
		tle3001c01v1Gpi2 OBJECT-TYPE
			SYNTAX Bit0Ina1Act
			MAX-ACCESS read-only
			STATUS current
			DESCRIPTION
				"GPI2 status"
		::= { tle3001c01v1Entry 33 }

		-- 1.3.6.1.4.1.10106.3.101291.1.1.34
		tle3001c01v1Gpi2TrapEnable OBJECT-TYPE
			SYNTAX AlarmEnable
			MAX-ACCESS read-write
			STATUS current
			DESCRIPTION
				"GPI2 status Trap Enable"
		::= { tle3001c01v1Entry 34 }

		-- 1.3.6.1.4.1.10106.3.101291.1.1.35
		tle3001c01v1Gpi3 OBJECT-TYPE
			SYNTAX Bit0Ina1Act
			MAX-ACCESS read-only
			STATUS current
			DESCRIPTION
				"GPI3 status"
		::= { tle3001c01v1Entry 35 }

		-- 1.3.6.1.4.1.10106.3.101291.1.1.36
		tle3001c01v1Gpi3TrapEnable OBJECT-TYPE
			SYNTAX AlarmEnable
			MAX-ACCESS read-write
			STATUS current
			DESCRIPTION
				"GPI3 status Trap Enable"
		::= { tle3001c01v1Entry 36 }

		-- 1.3.6.1.4.1.10106.3.101291.1.1.37
		tle3001c01v1Gpi4 OBJECT-TYPE
			SYNTAX Bit0Ina1Act
			MAX-ACCESS read-only
			STATUS current
			DESCRIPTION
				"GPI4 status"
		::= { tle3001c01v1Entry 37 }

		-- 1.3.6.1.4.1.10106.3.101291.1.1.38
		tle3001c01v1Gpi4TrapEnable OBJECT-TYPE
			SYNTAX AlarmEnable
			MAX-ACCESS read-write
			STATUS current
			DESCRIPTION
				"GPI4 status Trap Enable"
		::= { tle3001c01v1Entry 38 }

		-- 1.3.6.1.4.1.10106.3.101291.1.1.39
		tle3001c01v1RedBoard OBJECT-TYPE
			SYNTAX Bit0No1Yes
			MAX-ACCESS read-only
			STATUS current
			DESCRIPTION
				"Indicates that there are two modules in redundant configuration"
		::= { tle3001c01v1Entry 39 }

		-- 1.3.6.1.4.1.10106.3.101291.1.1.40
		tle3001c01v1RedBoardTrapEnable OBJECT-TYPE
			SYNTAX AlarmEnable
			MAX-ACCESS read-write
			STATUS current
			DESCRIPTION
				"Indicates that there are two modules in redundant configuration Trap Enable"
		::= { tle3001c01v1Entry 40 }

		-- 1.3.6.1.4.1.10106.3.101291.1.1.41
		tle3001c01v1EthLink OBJECT-TYPE
			SYNTAX Bit0No1Yes
			MAX-ACCESS read-only
			STATUS current
			DESCRIPTION
				"Indicates that the Ethernet link is OK"
		::= { tle3001c01v1Entry 41 }

		-- 1.3.6.1.4.1.10106.3.101291.1.1.42
		tle3001c01v1EthLinkTrapEnable OBJECT-TYPE
			SYNTAX AlarmEnable
			MAX-ACCESS read-write
			STATUS current
			DESCRIPTION
				"Indicates that the Ethernet link is OK Trap Enable"
		::= { tle3001c01v1Entry 42 }

		-- 1.3.6.1.4.1.10106.3.101291.1.1.43
		tle3001c01v1EthRedAct OBJECT-TYPE
			SYNTAX Bit0No1Yes
			MAX-ACCESS read-only
			STATUS current
			DESCRIPTION
				"Indicates that this is the active module of the redundant configuration"
		::= { tle3001c01v1Entry 43 }

		-- 1.3.6.1.4.1.10106.3.101291.1.1.44
		tle3001c01v1EthRedActTrapEnable OBJECT-TYPE
			SYNTAX AlarmEnable
			MAX-ACCESS read-write
			STATUS current
			DESCRIPTION
				"Indicates that this is the active module of the redundant configuration Trap Enable"
		::= { tle3001c01v1Entry 44 }

		-- 1.3.6.1.4.1.10106.3.101291.1.1.45
		tle3001c01v1App1Ena OBJECT-TYPE
			SYNTAX Bit0No1Yes
			MAX-ACCESS read-only
			STATUS current
			DESCRIPTION
				"Indicates the event log is enabled"
		::= { tle3001c01v1Entry 45 }

		-- 1.3.6.1.4.1.10106.3.101291.1.1.47
		tle3001c01v1App2Ena OBJECT-TYPE
			SYNTAX Bit0No1Yes
			MAX-ACCESS read-only
			STATUS current
			DESCRIPTION
				"Indicates the SNMP is enabled"
		::= { tle3001c01v1Entry 47 }

		-- 1.3.6.1.4.1.10106.3.101291.1.1.49
		tle3001c01v1App3Ena OBJECT-TYPE
			SYNTAX Bit0No1Yes
			MAX-ACCESS read-only
			STATUS current
			DESCRIPTION
				"Indicates the access control is enabled"
		::= { tle3001c01v1Entry 49 }

		-- 1.3.6.1.4.1.10106.3.101291.1.1.51
		tle3001c01v1App4Ena OBJECT-TYPE
			SYNTAX Bit0No1Yes
			MAX-ACCESS read-only
			STATUS current
			DESCRIPTION
				"Indicates the application 4 is enabled"
		::= { tle3001c01v1Entry 51 }

		-- 1.3.6.1.4.1.10106.3.101291.1.1.53
		tle3001c01v1App5Ena OBJECT-TYPE
			SYNTAX Bit0No1Yes
			MAX-ACCESS read-only
			STATUS current
			DESCRIPTION
				"Indicates the application 5 is enabled"
		::= { tle3001c01v1Entry 53 }

		-- 1.3.6.1.4.1.10106.3.101291.1.1.55
		tle3001c01v1App6Ena OBJECT-TYPE
			SYNTAX Bit0No1Yes
			MAX-ACCESS read-only
			STATUS current
			DESCRIPTION
				"Indicates the application 6 is enabled"
		::= { tle3001c01v1Entry 55 }

		-- 1.3.6.1.4.1.10106.3.101291.1.1.57
		tle3001c01v1App7Ena OBJECT-TYPE
			SYNTAX Bit0No1Yes
			MAX-ACCESS read-only
			STATUS current
			DESCRIPTION
				"Indicates the application 7 is enabled"
		::= { tle3001c01v1Entry 57 }

		-- 1.3.6.1.4.1.10106.3.101291.1.1.59
		tle3001c01v1App8Ena OBJECT-TYPE
			SYNTAX Bit0No1Yes
			MAX-ACCESS read-only
			STATUS current
			DESCRIPTION
				"Indicates the application 8 is enabled"
		::= { tle3001c01v1Entry 59 }

		-- 1.3.6.1.4.1.10106.3.101291.1.1.61
		tle3001c01v1App9Ena OBJECT-TYPE
			SYNTAX Bit0No1Yes
			MAX-ACCESS read-only
			STATUS current
			DESCRIPTION
				"Indicates the application 9 is enabled"
		::= { tle3001c01v1Entry 61 }

		-- 1.3.6.1.4.1.10106.3.101291.1.1.63
		tle3001c01v1App10Ena OBJECT-TYPE
			SYNTAX Bit0No1Yes
			MAX-ACCESS read-only
			STATUS current
			DESCRIPTION
				"Indicates the application 10 is enabled"
		::= { tle3001c01v1Entry 63 }

		-- 1.3.6.1.4.1.10106.3.101291.1.1.65
		tle3001c01v1App11Ena OBJECT-TYPE
			SYNTAX Bit0No1Yes
			MAX-ACCESS read-only
			STATUS current
			DESCRIPTION
				"Indicates the application 11 is enabled"
		::= { tle3001c01v1Entry 65 }

		-- 1.3.6.1.4.1.10106.3.101291.1.1.67
		tle3001c01v1App12Ena OBJECT-TYPE
			SYNTAX Bit0No1Yes
			MAX-ACCESS read-only
			STATUS current
			DESCRIPTION
				"Indicates the application 12 is enabled"
		::= { tle3001c01v1Entry 67 }

		-- 1.3.6.1.4.1.10106.3.101291.1.1.69
		tle3001c01v1App13Ena OBJECT-TYPE
			SYNTAX Bit0No1Yes
			MAX-ACCESS read-only
			STATUS current
			DESCRIPTION
				"Indicates the application 13 is enabled"
		::= { tle3001c01v1Entry 69 }

		-- 1.3.6.1.4.1.10106.3.101291.1.1.71
		tle3001c01v1App14Ena OBJECT-TYPE
			SYNTAX Bit0No1Yes
			MAX-ACCESS read-only
			STATUS current
			DESCRIPTION
				"Indicates the application 14 is enabled"
		::= { tle3001c01v1Entry 71 }

		-- 1.3.6.1.4.1.10106.3.101291.1.1.73
		tle3001c01v1App15Ena OBJECT-TYPE
			SYNTAX Bit0No1Yes
			MAX-ACCESS read-only
			STATUS current
			DESCRIPTION
				"Indicates the application 15 is enabled"
		::= { tle3001c01v1Entry 73 }

		-- 1.3.6.1.4.1.10106.3.101291.1.1.75
		tle3001c01v1App16Ena OBJECT-TYPE
			SYNTAX Bit0No1Yes
			MAX-ACCESS read-only
			STATUS current
			DESCRIPTION
				"Indicates the application 16 is enabled"
		::= { tle3001c01v1Entry 75 }

		-- 1.3.6.1.4.1.10106.3.101291.1.1.77
		tle3001c01v1SerialNo OBJECT-TYPE
			SYNTAX SerialNo
			MAX-ACCESS read-only
			STATUS current
			DESCRIPTION
				"Serial number"
		::= { tle3001c01v1Entry 77 }

		-- 1.3.6.1.4.1.10106.3.339901
		gvd3000c01v1 OBJECT IDENTIFIER ::= { albalaProducts 339901 }

		-- 1.3.6.1.4.1.10106.3.339901.1
		gvd3000c01v1Table  OBJECT-TYPE
			SYNTAX SEQUENCE OF Gvd3000c01v1Entry
			MAX-ACCESS not-accessible
			STATUS current
			DESCRIPTION
				"Module  GVD3000C01V1 Table"
			::= { gvd3000c01v1 1 }

		-- 1.3.6.1.4.1.10106.3.339901.1.1
		gvd3000c01v1Entry  OBJECT-TYPE
			SYNTAX Gvd3000c01v1Entry
			MAX-ACCESS not-accessible
			STATUS current
			DESCRIPTION
				"Module GVD3000C01V1 Entry"
			INDEX { gvd3000c01v1Index }
			::= { gvd3000c01v1Table 1 }

			Gvd3000c01v1Entry ::=
			SEQUENCE {
				gvd3000c01v1Index
				ModuleIndex,
				gvd3000c01v1SignalType
				Bit0G7031Oth,
				gvd3000c01v1G703Type
				Bit0E11E3,
				gvd3000c01v1LosA
				BitFail,
				gvd3000c01v1LosATrapEnable
				AlarmEnable,
				gvd3000c01v1AisA
				BitFail,
				gvd3000c01v1AisATrapEnable
				AlarmEnable,
				gvd3000c01v1LosB
				BitFail,
				gvd3000c01v1LosBTrapEnable
				AlarmEnable,
				gvd3000c01v1AisB
				BitFail,
				gvd3000c01v1AisBTrapEnable
				AlarmEnable,
				gvd3000c01v1SerialNo
				SerialNo
			 }

		-- 1.3.6.1.4.1.10106.3.101291.1.1.1
		gvd3000c01v1Index OBJECT-TYPE
			SYNTAX ModuleIndex
			MAX-ACCESS read-only
			STATUS current
			DESCRIPTION
				"Index of GVD3000C01V1 Table"
		::= { gvd3000c01v1Entry 1 }

		-- 1.3.6.1.4.1.10106.3.101291.1.1.3
		gvd3000c01v1SignalType OBJECT-TYPE
			SYNTAX Bit0G7031Oth
			MAX-ACCESS read-write
			STATUS current
			DESCRIPTION
				"Allows selecting the signal type"
		::= { gvd3000c01v1Entry 3 }

		-- 1.3.6.1.4.1.10106.3.101291.1.1.5
		gvd3000c01v1G703Type OBJECT-TYPE
			SYNTAX Bit0E11E3
			MAX-ACCESS read-write
			STATUS current
			DESCRIPTION
				"Allows selecting the G703 signal type"
		::= { gvd3000c01v1Entry 5 }

		-- 1.3.6.1.4.1.10106.3.101291.1.1.7
		gvd3000c01v1LosA OBJECT-TYPE
			SYNTAX BitFail
			MAX-ACCESS read-only
			STATUS current
			DESCRIPTION
				"Indicates that a LOS fail has been detected"
		::= { gvd3000c01v1Entry 7 }

		-- 1.3.6.1.4.1.10106.3.101291.1.1.8
		gvd3000c01v1LosATrapEnable OBJECT-TYPE
			SYNTAX AlarmEnable
			MAX-ACCESS read-write
			STATUS current
			DESCRIPTION
				"Indicates that a LOS fail has been detected Trap Enable"
		::= { gvd3000c01v1Entry 8 }

		-- 1.3.6.1.4.1.10106.3.101291.1.1.9
		gvd3000c01v1AisA OBJECT-TYPE
			SYNTAX BitFail
			MAX-ACCESS read-only
			STATUS current
			DESCRIPTION
				"Indicates that a AIS fail has been detected"
		::= { gvd3000c01v1Entry 9 }

		-- 1.3.6.1.4.1.10106.3.101291.1.1.10
		gvd3000c01v1AisATrapEnable OBJECT-TYPE
			SYNTAX AlarmEnable
			MAX-ACCESS read-write
			STATUS current
			DESCRIPTION
				"Indicates that a AIS fail has been detected Trap Enable"
		::= { gvd3000c01v1Entry 10 }

		-- 1.3.6.1.4.1.10106.3.101291.1.1.11
		gvd3000c01v1LosB OBJECT-TYPE
			SYNTAX BitFail
			MAX-ACCESS read-only
			STATUS current
			DESCRIPTION
				"Indicates that a LOS fail has been detected"
		::= { gvd3000c01v1Entry 11 }

		-- 1.3.6.1.4.1.10106.3.101291.1.1.12
		gvd3000c01v1LosBTrapEnable OBJECT-TYPE
			SYNTAX AlarmEnable
			MAX-ACCESS read-write
			STATUS current
			DESCRIPTION
				"Indicates that a LOS fail has been detected Trap Enable"
		::= { gvd3000c01v1Entry 12 }

		-- 1.3.6.1.4.1.10106.3.101291.1.1.13
		gvd3000c01v1AisB OBJECT-TYPE
			SYNTAX BitFail
			MAX-ACCESS read-only
			STATUS current
			DESCRIPTION
				"Indicates that a AIS fail has been detected"
		::= { gvd3000c01v1Entry 13 }

		-- 1.3.6.1.4.1.10106.3.101291.1.1.14
		gvd3000c01v1AisBTrapEnable OBJECT-TYPE
			SYNTAX AlarmEnable
			MAX-ACCESS read-write
			STATUS current
			DESCRIPTION
				"Indicates that a AIS fail has been detected Trap Enable"
		::= { gvd3000c01v1Entry 14 }

		-- 1.3.6.1.4.1.10106.3.101291.1.1.15
		gvd3000c01v1SerialNo OBJECT-TYPE
			SYNTAX SerialNo
			MAX-ACCESS read-only
			STATUS current
			DESCRIPTION
				"Serial number"
		::= { gvd3000c01v1Entry 15 }

		-- 1.3.6.1.4.1.10106.3.343901
		htg3000c01v1 OBJECT IDENTIFIER ::= { albalaProducts 343901 }

		-- 1.3.6.1.4.1.10106.3.343901.1
		htg3000c01v1Table  OBJECT-TYPE
			SYNTAX SEQUENCE OF Htg3000c01v1Entry
			MAX-ACCESS not-accessible
			STATUS current
			DESCRIPTION
				"Module  HTG3000C01V1 Table"
			::= { htg3000c01v1 1 }

		-- 1.3.6.1.4.1.10106.3.343901.1.1
		htg3000c01v1Entry  OBJECT-TYPE
			SYNTAX Htg3000c01v1Entry
			MAX-ACCESS not-accessible
			STATUS current
			DESCRIPTION
				"Module HTG3000C01V1 Entry"
			INDEX { htg3000c01v1Index }
			::= { htg3000c01v1Table 1 }

			Htg3000c01v1Entry ::=
			SEQUENCE {
				htg3000c01v1Index
				ModuleIndex,
				htg3000c01v1AnaRefOutFmt
				SdiHd3gFmt1,
				htg3000c01v1DigOutFmt
				SdiHd3gFmt1,
				htg3000c01v1ColourDis
				Bit0Ena1Dis,
				htg3000c01v1EdhDis
				Bit0Ena1Dis,
				htg3000c01v1Smpte352Dis
				Bit0Ena1Dis,
				htg3000c01v1GenlockMode
				GenlockMode1,
				htg3000c01v1HDelayMain
				DelayPixel4,
				htg3000c01v1VDelayMain
				DelayLines2,
				htg3000c01v1HDelayAux
				DelayPixel3,
				htg3000c01v1VDelayAux
				DelayLines1,
				htg3000c01v1TestSignal
				Uint6,
				htg3000c01v1RefLckFail
				BitFail,
				htg3000c01v1RefLckFailTrapEnable
				AlarmEnable,
				htg3000c01v1RefFail
				BitFail,
				htg3000c01v1RefFailTrapEnable
				AlarmEnable,
				htg3000c01v1AnaRefPres
				Bit0No1Yes,
				htg3000c01v1DigRefPres
				Bit0No1Yes,
				htg3000c01v1IntRefPres
				Bit0No1Yes,
				htg3000c01v1IncRefMain
				Incompatibility,
				htg3000c01v1IncRefAux
				Incompatibility,
				htg3000c01v1DigRefFmt
				SdiHd3gFmt2,
				htg3000c01v1SerialNo
				SerialNo
			 }

		-- 1.3.6.1.4.1.10106.3.101291.1.1.1
		htg3000c01v1Index OBJECT-TYPE
			SYNTAX ModuleIndex
			MAX-ACCESS read-only
			STATUS current
			DESCRIPTION
				"Index of HTG3000C01V1 Table"
		::= { htg3000c01v1Entry 1 }

		-- 1.3.6.1.4.1.10106.3.101291.1.1.3
		htg3000c01v1AnaRefOutFmt OBJECT-TYPE
			SYNTAX SdiHd3gFmt1
			MAX-ACCESS read-write
			STATUS current
			DESCRIPTION
				"Analog reference input format"
		::= { htg3000c01v1Entry 3 }

		-- 1.3.6.1.4.1.10106.3.101291.1.1.5
		htg3000c01v1DigOutFmt OBJECT-TYPE
			SYNTAX SdiHd3gFmt1
			MAX-ACCESS read-write
			STATUS current
			DESCRIPTION
				"Digital output format"
		::= { htg3000c01v1Entry 5 }

		-- 1.3.6.1.4.1.10106.3.101291.1.1.7
		htg3000c01v1ColourDis OBJECT-TYPE
			SYNTAX Bit0Ena1Dis
			MAX-ACCESS read-write
			STATUS current
			DESCRIPTION
				"Allows disabling colour"
		::= { htg3000c01v1Entry 7 }

		-- 1.3.6.1.4.1.10106.3.101291.1.1.9
		htg3000c01v1EdhDis OBJECT-TYPE
			SYNTAX Bit0Ena1Dis
			MAX-ACCESS read-write
			STATUS current
			DESCRIPTION
				"Allows disabling EDH packet insertion"
		::= { htg3000c01v1Entry 9 }

		-- 1.3.6.1.4.1.10106.3.101291.1.1.11
		htg3000c01v1Smpte352Dis OBJECT-TYPE
			SYNTAX Bit0Ena1Dis
			MAX-ACCESS read-write
			STATUS current
			DESCRIPTION
				"Allows disabling SMPTE 352 packet insertion"
		::= { htg3000c01v1Entry 11 }

		-- 1.3.6.1.4.1.10106.3.101291.1.1.13
		htg3000c01v1GenlockMode OBJECT-TYPE
			SYNTAX GenlockMode1
			MAX-ACCESS read-write
			STATUS current
			DESCRIPTION
				"Allos selecting the reference input signal"
		::= { htg3000c01v1Entry 13 }

		-- 1.3.6.1.4.1.10106.3.101291.1.1.15
		htg3000c01v1HDelayMain OBJECT-TYPE
			SYNTAX DelayPixel4
			MAX-ACCESS read-write
			STATUS current
			DESCRIPTION
				"Allows adjusting the video horizontal delay of main output"
		::= { htg3000c01v1Entry 15 }

		-- 1.3.6.1.4.1.10106.3.101291.1.1.17
		htg3000c01v1VDelayMain OBJECT-TYPE
			SYNTAX DelayLines2
			MAX-ACCESS read-write
			STATUS current
			DESCRIPTION
				"Allows adjusting the video vertical delay of main output"
		::= { htg3000c01v1Entry 17 }

		-- 1.3.6.1.4.1.10106.3.101291.1.1.19
		htg3000c01v1HDelayAux OBJECT-TYPE
			SYNTAX DelayPixel3
			MAX-ACCESS read-write
			STATUS current
			DESCRIPTION
				"Allows adjusting the video horizontal delay of auxiliary output"
		::= { htg3000c01v1Entry 19 }

		-- 1.3.6.1.4.1.10106.3.101291.1.1.21
		htg3000c01v1VDelayAux OBJECT-TYPE
			SYNTAX DelayLines1
			MAX-ACCESS read-write
			STATUS current
			DESCRIPTION
				"Allows adjusting the video vertical delay of auxiliary output"
		::= { htg3000c01v1Entry 21 }

		-- 1.3.6.1.4.1.10106.3.101291.1.1.23
		htg3000c01v1TestSignal OBJECT-TYPE
			SYNTAX Uint6
			MAX-ACCESS read-write
			STATUS current
			DESCRIPTION
				"Allows selecting the generated video signal pattern"
		::= { htg3000c01v1Entry 23 }

		-- 1.3.6.1.4.1.10106.3.101291.1.1.25
		htg3000c01v1RefLckFail OBJECT-TYPE
			SYNTAX BitFail
			MAX-ACCESS read-only
			STATUS current
			DESCRIPTION
				"Indicates that the module is not locked to the reference"
		::= { htg3000c01v1Entry 25 }

		-- 1.3.6.1.4.1.10106.3.101291.1.1.26
		htg3000c01v1RefLckFailTrapEnable OBJECT-TYPE
			SYNTAX AlarmEnable
			MAX-ACCESS read-write
			STATUS current
			DESCRIPTION
				"Indicates that the module is not locked to the reference Trap Enable"
		::= { htg3000c01v1Entry 26 }

		-- 1.3.6.1.4.1.10106.3.101291.1.1.27
		htg3000c01v1RefFail OBJECT-TYPE
			SYNTAX BitFail
			MAX-ACCESS read-only
			STATUS current
			DESCRIPTION
				"Indicates that there is no reference input signal"
		::= { htg3000c01v1Entry 27 }

		-- 1.3.6.1.4.1.10106.3.101291.1.1.28
		htg3000c01v1RefFailTrapEnable OBJECT-TYPE
			SYNTAX AlarmEnable
			MAX-ACCESS read-write
			STATUS current
			DESCRIPTION
				"Indicates that there is no reference input signal Trap Enable"
		::= { htg3000c01v1Entry 28 }

		-- 1.3.6.1.4.1.10106.3.101291.1.1.29
		htg3000c01v1AnaRefPres OBJECT-TYPE
			SYNTAX Bit0No1Yes
			MAX-ACCESS read-only
			STATUS current
			DESCRIPTION
				"Indicates the analog reference presence"
		::= { htg3000c01v1Entry 29 }

		-- 1.3.6.1.4.1.10106.3.101291.1.1.31
		htg3000c01v1DigRefPres OBJECT-TYPE
			SYNTAX Bit0No1Yes
			MAX-ACCESS read-only
			STATUS current
			DESCRIPTION
				"Indicates the digital reference presence"
		::= { htg3000c01v1Entry 31 }

		-- 1.3.6.1.4.1.10106.3.101291.1.1.33
		htg3000c01v1IntRefPres OBJECT-TYPE
			SYNTAX Bit0No1Yes
			MAX-ACCESS read-only
			STATUS current
			DESCRIPTION
				"Indicates the internal reference presence"
		::= { htg3000c01v1Entry 33 }

		-- 1.3.6.1.4.1.10106.3.101291.1.1.35
		htg3000c01v1IncRefMain OBJECT-TYPE
			SYNTAX Incompatibility
			MAX-ACCESS read-only
			STATUS current
			DESCRIPTION
				"Indicates that the reference and the main output are not compatible"
		::= { htg3000c01v1Entry 35 }

		-- 1.3.6.1.4.1.10106.3.101291.1.1.37
		htg3000c01v1IncRefAux OBJECT-TYPE
			SYNTAX Incompatibility
			MAX-ACCESS read-only
			STATUS current
			DESCRIPTION
				"Indicates that the main output and the auxiliary output are not compatible"
		::= { htg3000c01v1Entry 37 }

		-- 1.3.6.1.4.1.10106.3.101291.1.1.39
		htg3000c01v1DigRefFmt OBJECT-TYPE
			SYNTAX SdiHd3gFmt2
			MAX-ACCESS read-only
			STATUS current
			DESCRIPTION
				"Inidcates the digital reference input detected format"
		::= { htg3000c01v1Entry 39 }

		-- 1.3.6.1.4.1.10106.3.101291.1.1.41
		htg3000c01v1SerialNo OBJECT-TYPE
			SYNTAX SerialNo
			MAX-ACCESS read-only
			STATUS current
			DESCRIPTION
				"Serial number"
		::= { htg3000c01v1Entry 41 }

		-- 1.3.6.1.4.1.10106.3.347601
		hvd3001c01v1 OBJECT IDENTIFIER ::= { albalaProducts 347601 }

		-- 1.3.6.1.4.1.10106.3.347601.1
		hvd3001c01v1Table  OBJECT-TYPE
			SYNTAX SEQUENCE OF Hvd3001c01v1Entry
			MAX-ACCESS not-accessible
			STATUS current
			DESCRIPTION
				"Module  HVD3001C01V1 Table"
			::= { hvd3001c01v1 1 }

		-- 1.3.6.1.4.1.10106.3.347601.1.1
		hvd3001c01v1Entry  OBJECT-TYPE
			SYNTAX Hvd3001c01v1Entry
			MAX-ACCESS not-accessible
			STATUS current
			DESCRIPTION
				"Module HVD3001C01V1 Entry"
			INDEX { hvd3001c01v1Index }
			::= { hvd3001c01v1Table 1 }

			Hvd3001c01v1Entry ::=
			SEQUENCE {
				hvd3001c01v1Index
				ModuleIndex,
				hvd3001c01v1OpElecNA
				Bit0Ele1Opt,
				hvd3001c01v1OpElecNB
				Bit0Ele1Opt,
				hvd3001c01v1Mode
				BitDistrib1,
				hvd3001c01v1NoSigA
				BitFail,
				hvd3001c01v1NoSigATrapEnable
				AlarmEnable,
				hvd3001c01v1UnlockA
				BitFail,
				hvd3001c01v1UnlockATrapEnable
				AlarmEnable,
				hvd3001c01v1LFailA
				BitFail,
				hvd3001c01v1LFailATrapEnable
				AlarmEnable,
				hvd3001c01v1HdA
				Bit0Sd1Hd,
				hvd3001c01v1NoElecA
				BitFail,
				hvd3001c01v1NoOpticA
				BitFail,
				hvd3001c01v1NoSigB
				BitFail,
				hvd3001c01v1NoSigBTrapEnable
				AlarmEnable,
				hvd3001c01v1UnlockB
				BitFail,
				hvd3001c01v1UnlockBTrapEnable
				AlarmEnable,
				hvd3001c01v1LFailB
				BitFail,
				hvd3001c01v1LFailBTrapEnable
				AlarmEnable,
				hvd3001c01v1HdB
				Bit0Sd1Hd,
				hvd3001c01v1NoElecB
				BitFail,
				hvd3001c01v1NoOpticB
				BitFail,
				hvd3001c01v1OpTxPres
				Bit0No1Yes,
				hvd3001c01v1OpRxPres
				Bit0No1Yes,
				hvd3001c01v1SfpTxSn
				SerialNo,
				hvd3001c01v1SfpRxSn
				SerialNo,
				hvd3001c01v1SerialNo
				SerialNo
			 }

		-- 1.3.6.1.4.1.10106.3.101291.1.1.1
		hvd3001c01v1Index OBJECT-TYPE
			SYNTAX ModuleIndex
			MAX-ACCESS read-only
			STATUS current
			DESCRIPTION
				"Index of HVD3001C01V1 Table"
		::= { hvd3001c01v1Entry 1 }

		-- 1.3.6.1.4.1.10106.3.101291.1.1.3
		hvd3001c01v1OpElecNA OBJECT-TYPE
			SYNTAX Bit0Ele1Opt
			MAX-ACCESS read-write
			STATUS current
			DESCRIPTION
				"Indicates the input selected"
		::= { hvd3001c01v1Entry 3 }

		-- 1.3.6.1.4.1.10106.3.101291.1.1.5
		hvd3001c01v1OpElecNB OBJECT-TYPE
			SYNTAX Bit0Ele1Opt
			MAX-ACCESS read-write
			STATUS current
			DESCRIPTION
				"Indicates the input selected"
		::= { hvd3001c01v1Entry 5 }

		-- 1.3.6.1.4.1.10106.3.101291.1.1.7
		hvd3001c01v1Mode OBJECT-TYPE
			SYNTAX BitDistrib1
			MAX-ACCESS read-write
			STATUS current
			DESCRIPTION
				"Operating mode"
		::= { hvd3001c01v1Entry 7 }

		-- 1.3.6.1.4.1.10106.3.101291.1.1.9
		hvd3001c01v1NoSigA OBJECT-TYPE
			SYNTAX BitFail
			MAX-ACCESS read-only
			STATUS current
			DESCRIPTION
				"Input signal status"
		::= { hvd3001c01v1Entry 9 }

		-- 1.3.6.1.4.1.10106.3.101291.1.1.10
		hvd3001c01v1NoSigATrapEnable OBJECT-TYPE
			SYNTAX AlarmEnable
			MAX-ACCESS read-write
			STATUS current
			DESCRIPTION
				"Input signal status Trap Enable"
		::= { hvd3001c01v1Entry 10 }

		-- 1.3.6.1.4.1.10106.3.101291.1.1.11
		hvd3001c01v1UnlockA OBJECT-TYPE
			SYNTAX BitFail
			MAX-ACCESS read-only
			STATUS current
			DESCRIPTION
				"Indicates signal unlock fail"
		::= { hvd3001c01v1Entry 11 }

		-- 1.3.6.1.4.1.10106.3.101291.1.1.12
		hvd3001c01v1UnlockATrapEnable OBJECT-TYPE
			SYNTAX AlarmEnable
			MAX-ACCESS read-write
			STATUS current
			DESCRIPTION
				"Indicates signal unlock fail Trap Enable"
		::= { hvd3001c01v1Entry 12 }

		-- 1.3.6.1.4.1.10106.3.101291.1.1.13
		hvd3001c01v1LFailA OBJECT-TYPE
			SYNTAX BitFail
			MAX-ACCESS read-only
			STATUS current
			DESCRIPTION
				"Indicates a fail in laser"
		::= { hvd3001c01v1Entry 13 }

		-- 1.3.6.1.4.1.10106.3.101291.1.1.14
		hvd3001c01v1LFailATrapEnable OBJECT-TYPE
			SYNTAX AlarmEnable
			MAX-ACCESS read-write
			STATUS current
			DESCRIPTION
				"Indicates a fail in laser Trap Enable"
		::= { hvd3001c01v1Entry 14 }

		-- 1.3.6.1.4.1.10106.3.101291.1.1.15
		hvd3001c01v1HdA OBJECT-TYPE
			SYNTAX Bit0Sd1Hd
			MAX-ACCESS read-only
			STATUS current
			DESCRIPTION
				"Indicates the SDI signal type"
		::= { hvd3001c01v1Entry 15 }

		-- 1.3.6.1.4.1.10106.3.101291.1.1.17
		hvd3001c01v1NoElecA OBJECT-TYPE
			SYNTAX BitFail
			MAX-ACCESS read-only
			STATUS current
			DESCRIPTION
				"Electrical input signal status"
		::= { hvd3001c01v1Entry 17 }

		-- 1.3.6.1.4.1.10106.3.101291.1.1.19
		hvd3001c01v1NoOpticA OBJECT-TYPE
			SYNTAX BitFail
			MAX-ACCESS read-only
			STATUS current
			DESCRIPTION
				"Optical input signal status"
		::= { hvd3001c01v1Entry 19 }

		-- 1.3.6.1.4.1.10106.3.101291.1.1.21
		hvd3001c01v1NoSigB OBJECT-TYPE
			SYNTAX BitFail
			MAX-ACCESS read-only
			STATUS current
			DESCRIPTION
				"Input signal status"
		::= { hvd3001c01v1Entry 21 }

		-- 1.3.6.1.4.1.10106.3.101291.1.1.22
		hvd3001c01v1NoSigBTrapEnable OBJECT-TYPE
			SYNTAX AlarmEnable
			MAX-ACCESS read-write
			STATUS current
			DESCRIPTION
				"Input signal status Trap Enable"
		::= { hvd3001c01v1Entry 22 }

		-- 1.3.6.1.4.1.10106.3.101291.1.1.23
		hvd3001c01v1UnlockB OBJECT-TYPE
			SYNTAX BitFail
			MAX-ACCESS read-only
			STATUS current
			DESCRIPTION
				"Indicates signal unlock fail"
		::= { hvd3001c01v1Entry 23 }

		-- 1.3.6.1.4.1.10106.3.101291.1.1.24
		hvd3001c01v1UnlockBTrapEnable OBJECT-TYPE
			SYNTAX AlarmEnable
			MAX-ACCESS read-write
			STATUS current
			DESCRIPTION
				"Indicates signal unlock fail Trap Enable"
		::= { hvd3001c01v1Entry 24 }

		-- 1.3.6.1.4.1.10106.3.101291.1.1.25
		hvd3001c01v1LFailB OBJECT-TYPE
			SYNTAX BitFail
			MAX-ACCESS read-only
			STATUS current
			DESCRIPTION
				"Indicates a fail in laser"
		::= { hvd3001c01v1Entry 25 }

		-- 1.3.6.1.4.1.10106.3.101291.1.1.26
		hvd3001c01v1LFailBTrapEnable OBJECT-TYPE
			SYNTAX AlarmEnable
			MAX-ACCESS read-write
			STATUS current
			DESCRIPTION
				"Indicates a fail in laser Trap Enable"
		::= { hvd3001c01v1Entry 26 }

		-- 1.3.6.1.4.1.10106.3.101291.1.1.27
		hvd3001c01v1HdB OBJECT-TYPE
			SYNTAX Bit0Sd1Hd
			MAX-ACCESS read-only
			STATUS current
			DESCRIPTION
				"Indicates the SDI signal type"
		::= { hvd3001c01v1Entry 27 }

		-- 1.3.6.1.4.1.10106.3.101291.1.1.29
		hvd3001c01v1NoElecB OBJECT-TYPE
			SYNTAX BitFail
			MAX-ACCESS read-only
			STATUS current
			DESCRIPTION
				"Electrical input signal status"
		::= { hvd3001c01v1Entry 29 }

		-- 1.3.6.1.4.1.10106.3.101291.1.1.31
		hvd3001c01v1NoOpticB OBJECT-TYPE
			SYNTAX BitFail
			MAX-ACCESS read-only
			STATUS current
			DESCRIPTION
				"Optical input signal status"
		::= { hvd3001c01v1Entry 31 }

		-- 1.3.6.1.4.1.10106.3.101291.1.1.33
		hvd3001c01v1OpTxPres OBJECT-TYPE
			SYNTAX Bit0No1Yes
			MAX-ACCESS read-only
			STATUS current
			DESCRIPTION
				"Indicates the presence of a SFP TX module"
		::= { hvd3001c01v1Entry 33 }

		-- 1.3.6.1.4.1.10106.3.101291.1.1.35
		hvd3001c01v1OpRxPres OBJECT-TYPE
			SYNTAX Bit0No1Yes
			MAX-ACCESS read-only
			STATUS current
			DESCRIPTION
				"Indicates the presence of a SFP RX module"
		::= { hvd3001c01v1Entry 35 }

		-- 1.3.6.1.4.1.10106.3.101291.1.1.37
		hvd3001c01v1SfpTxSn OBJECT-TYPE
			SYNTAX SerialNo
			MAX-ACCESS read-only
			STATUS current
			DESCRIPTION
				"SFP TX Serial number"
		::= { hvd3001c01v1Entry 37 }

		-- 1.3.6.1.4.1.10106.3.101291.1.1.39
		hvd3001c01v1SfpRxSn OBJECT-TYPE
			SYNTAX SerialNo
			MAX-ACCESS read-only
			STATUS current
			DESCRIPTION
				"SFP RX Serial number"
		::= { hvd3001c01v1Entry 39 }

		-- 1.3.6.1.4.1.10106.3.101291.1.1.41
		hvd3001c01v1SerialNo OBJECT-TYPE
			SYNTAX SerialNo
			MAX-ACCESS read-only
			STATUS current
			DESCRIPTION
				"Serial number"
		::= { hvd3001c01v1Entry 41 }

		-- 1.3.6.1.4.1.10106.3.350401
		vct3000c13v1 OBJECT IDENTIFIER ::= { albalaProducts 350401 }

		-- 1.3.6.1.4.1.10106.3.350401.1
		vct3000c13v1Table  OBJECT-TYPE
			SYNTAX SEQUENCE OF Vct3000c13v1Entry
			MAX-ACCESS not-accessible
			STATUS current
			DESCRIPTION
				"Module  VCT3000C13V1 Table"
			::= { vct3000c13v1 1 }

		-- 1.3.6.1.4.1.10106.3.350401.1.1
		vct3000c13v1Entry  OBJECT-TYPE
			SYNTAX Vct3000c13v1Entry
			MAX-ACCESS not-accessible
			STATUS current
			DESCRIPTION
				"Module VCT3000C13V1 Entry"
			INDEX { vct3000c13v1Index }
			::= { vct3000c13v1Table 1 }

			Vct3000c13v1Entry ::=
			SEQUENCE {
				vct3000c13v1Index
				ModuleIndex,
				vct3000c13v1Mode
				ChgOverMode2,
				vct3000c13v1ModeTrapEnable
				AlarmEnable,
				vct3000c13v1Buzzer
				BitMask,
				vct3000c13v1Input
				ChgOverInput1,
				vct3000c13v1InputTrapEnable
				AlarmEnable,
				vct3000c13v1InputChange
				Bit0No1Yes,
				vct3000c13v1RemoteEnable
				Bit0No1Yes,
				vct3000c13v1MainFail
				BitFail,
				vct3000c13v1MainFailTrapEnable
				AlarmEnable,
				vct3000c13v1ResFail
				BitFail,
				vct3000c13v1ResFailTrapEnable
				AlarmEnable,
				vct3000c13v1AuxFail
				BitFail,
				vct3000c13v1AuxFailTrapEnable
				AlarmEnable,
				vct3000c13v1Remote
				Bit0No1Yes,
				vct3000c13v1SerialNo
				SerialNo
			 }

		-- 1.3.6.1.4.1.10106.3.101291.1.1.1
		vct3000c13v1Index OBJECT-TYPE
			SYNTAX ModuleIndex
			MAX-ACCESS read-only
			STATUS current
			DESCRIPTION
				"Index of VCT3000C13V1 Table"
		::= { vct3000c13v1Entry 1 }

		-- 1.3.6.1.4.1.10106.3.101291.1.1.3
		vct3000c13v1Mode OBJECT-TYPE
			SYNTAX ChgOverMode2
			MAX-ACCESS read-write
			STATUS current
			DESCRIPTION
				"Allows selecting the switching mode"
		::= { vct3000c13v1Entry 3 }

		-- 1.3.6.1.4.1.10106.3.101291.1.1.4
		vct3000c13v1ModeTrapEnable OBJECT-TYPE
			SYNTAX AlarmEnable
			MAX-ACCESS read-write
			STATUS current
			DESCRIPTION
				"Allows selecting the switching mode Trap Enable"
		::= { vct3000c13v1Entry 4 }

		-- 1.3.6.1.4.1.10106.3.101291.1.1.5
		vct3000c13v1Buzzer OBJECT-TYPE
			SYNTAX BitMask
			MAX-ACCESS read-write
			STATUS current
			DESCRIPTION
				"Allows buzzer operation"
		::= { vct3000c13v1Entry 5 }

		-- 1.3.6.1.4.1.10106.3.101291.1.1.7
		vct3000c13v1Input OBJECT-TYPE
			SYNTAX ChgOverInput1
			MAX-ACCESS read-write
			STATUS current
			DESCRIPTION
				"Selected input"
		::= { vct3000c13v1Entry 7 }

		-- 1.3.6.1.4.1.10106.3.101291.1.1.8
		vct3000c13v1InputTrapEnable OBJECT-TYPE
			SYNTAX AlarmEnable
			MAX-ACCESS read-write
			STATUS current
			DESCRIPTION
				"Selected input Trap Enable"
		::= { vct3000c13v1Entry 8 }

		-- 1.3.6.1.4.1.10106.3.101291.1.1.9
		vct3000c13v1InputChange OBJECT-TYPE
			SYNTAX Bit0No1Yes
			MAX-ACCESS read-write
			STATUS current
			DESCRIPTION
				"Signals a change in selected input"
		::= { vct3000c13v1Entry 9 }

		-- 1.3.6.1.4.1.10106.3.101291.1.1.11
		vct3000c13v1RemoteEnable OBJECT-TYPE
			SYNTAX Bit0No1Yes
			MAX-ACCESS read-write
			STATUS current
			DESCRIPTION
				"Allows module to be GPI controlled"
		::= { vct3000c13v1Entry 11 }

		-- 1.3.6.1.4.1.10106.3.101291.1.1.13
		vct3000c13v1MainFail OBJECT-TYPE
			SYNTAX BitFail
			MAX-ACCESS read-only
			STATUS current
			DESCRIPTION
				"Main input status"
		::= { vct3000c13v1Entry 13 }

		-- 1.3.6.1.4.1.10106.3.101291.1.1.14
		vct3000c13v1MainFailTrapEnable OBJECT-TYPE
			SYNTAX AlarmEnable
			MAX-ACCESS read-write
			STATUS current
			DESCRIPTION
				"Main input status Trap Enable"
		::= { vct3000c13v1Entry 14 }

		-- 1.3.6.1.4.1.10106.3.101291.1.1.15
		vct3000c13v1ResFail OBJECT-TYPE
			SYNTAX BitFail
			MAX-ACCESS read-only
			STATUS current
			DESCRIPTION
				"Reserve input status"
		::= { vct3000c13v1Entry 15 }

		-- 1.3.6.1.4.1.10106.3.101291.1.1.16
		vct3000c13v1ResFailTrapEnable OBJECT-TYPE
			SYNTAX AlarmEnable
			MAX-ACCESS read-write
			STATUS current
			DESCRIPTION
				"Reserve input status Trap Enable"
		::= { vct3000c13v1Entry 16 }

		-- 1.3.6.1.4.1.10106.3.101291.1.1.17
		vct3000c13v1AuxFail OBJECT-TYPE
			SYNTAX BitFail
			MAX-ACCESS read-only
			STATUS current
			DESCRIPTION
				"Auxiliar input status"
		::= { vct3000c13v1Entry 17 }

		-- 1.3.6.1.4.1.10106.3.101291.1.1.18
		vct3000c13v1AuxFailTrapEnable OBJECT-TYPE
			SYNTAX AlarmEnable
			MAX-ACCESS read-write
			STATUS current
			DESCRIPTION
				"Auxiliar input status Trap Enable"
		::= { vct3000c13v1Entry 18 }

		-- 1.3.6.1.4.1.10106.3.101291.1.1.19
		vct3000c13v1Remote OBJECT-TYPE
			SYNTAX Bit0No1Yes
			MAX-ACCESS read-only
			STATUS current
			DESCRIPTION
				"Indicates when the module is GPI controlled"
		::= { vct3000c13v1Entry 19 }

		-- 1.3.6.1.4.1.10106.3.101291.1.1.21
		vct3000c13v1SerialNo OBJECT-TYPE
			SYNTAX SerialNo
			MAX-ACCESS read-only
			STATUS current
			DESCRIPTION
				"Serial number"
		::= { vct3000c13v1Entry 21 }

		-- 1.3.6.1.4.1.10106.3.352201
		dad3002c02v1 OBJECT IDENTIFIER ::= { albalaProducts 352201 }

		-- 1.3.6.1.4.1.10106.3.352201.1
		dad3002c02v1Table  OBJECT-TYPE
			SYNTAX SEQUENCE OF Dad3002c02v1Entry
			MAX-ACCESS not-accessible
			STATUS current
			DESCRIPTION
				"Module  DAD3002C02V1 Table"
			::= { dad3002c02v1 1 }

		-- 1.3.6.1.4.1.10106.3.352201.1.1
		dad3002c02v1Entry  OBJECT-TYPE
			SYNTAX Dad3002c02v1Entry
			MAX-ACCESS not-accessible
			STATUS current
			DESCRIPTION
				"Module DAD3002C02V1 Entry"
			INDEX { dad3002c02v1Index }
			::= { dad3002c02v1Table 1 }

			Dad3002c02v1Entry ::=
			SEQUENCE {
				dad3002c02v1Index
				ModuleIndex,
				dad3002c02v1LosA
				BitFail,
				dad3002c02v1LosATrapEnable
				AlarmEnable,
				dad3002c02v1LosB
				BitFail,
				dad3002c02v1LosBTrapEnable
				AlarmEnable,
				dad3002c02v1SerialNo
				SerialNo
			 }

		-- 1.3.6.1.4.1.10106.3.101291.1.1.1
		dad3002c02v1Index OBJECT-TYPE
			SYNTAX ModuleIndex
			MAX-ACCESS read-only
			STATUS current
			DESCRIPTION
				"Index of DAD3002C02V1 Table"
		::= { dad3002c02v1Entry 1 }

		-- 1.3.6.1.4.1.10106.3.101291.1.1.3
		dad3002c02v1LosA OBJECT-TYPE
			SYNTAX BitFail
			MAX-ACCESS read-only
			STATUS current
			DESCRIPTION
				"Indicates that a LOS fail has been detected"
		::= { dad3002c02v1Entry 3 }

		-- 1.3.6.1.4.1.10106.3.101291.1.1.4
		dad3002c02v1LosATrapEnable OBJECT-TYPE
			SYNTAX AlarmEnable
			MAX-ACCESS read-write
			STATUS current
			DESCRIPTION
				"Indicates that a LOS fail has been detected Trap Enable"
		::= { dad3002c02v1Entry 4 }

		-- 1.3.6.1.4.1.10106.3.101291.1.1.5
		dad3002c02v1LosB OBJECT-TYPE
			SYNTAX BitFail
			MAX-ACCESS read-only
			STATUS current
			DESCRIPTION
				"Indicates that a LOS fail has been detected"
		::= { dad3002c02v1Entry 5 }

		-- 1.3.6.1.4.1.10106.3.101291.1.1.6
		dad3002c02v1LosBTrapEnable OBJECT-TYPE
			SYNTAX AlarmEnable
			MAX-ACCESS read-write
			STATUS current
			DESCRIPTION
				"Indicates that a LOS fail has been detected Trap Enable"
		::= { dad3002c02v1Entry 6 }

		-- 1.3.6.1.4.1.10106.3.101291.1.1.7
		dad3002c02v1SerialNo OBJECT-TYPE
			SYNTAX SerialNo
			MAX-ACCESS read-only
			STATUS current
			DESCRIPTION
				"Serial number"
		::= { dad3002c02v1Entry 7 }

		-- 1.3.6.1.4.1.10106.3.353101
		hvd3001c02v1 OBJECT IDENTIFIER ::= { albalaProducts 353101 }

		-- 1.3.6.1.4.1.10106.3.353101.1
		hvd3001c02v1Table  OBJECT-TYPE
			SYNTAX SEQUENCE OF Hvd3001c02v1Entry
			MAX-ACCESS not-accessible
			STATUS current
			DESCRIPTION
				"Module  HVD3001C02V1 Table"
			::= { hvd3001c02v1 1 }

		-- 1.3.6.1.4.1.10106.3.353101.1.1
		hvd3001c02v1Entry  OBJECT-TYPE
			SYNTAX Hvd3001c02v1Entry
			MAX-ACCESS not-accessible
			STATUS current
			DESCRIPTION
				"Module HVD3001C02V1 Entry"
			INDEX { hvd3001c02v1Index }
			::= { hvd3001c02v1Table 1 }

			Hvd3001c02v1Entry ::=
			SEQUENCE {
				hvd3001c02v1Index
				ModuleIndex,
				hvd3001c02v1OpElecNA
				Bit0Ele1Opt,
				hvd3001c02v1OpElecNB
				Bit0Ele1Opt,
				hvd3001c02v1Mode
				BitDistrib1,
				hvd3001c02v1NoSigA
				BitFail,
				hvd3001c02v1NoSigATrapEnable
				AlarmEnable,
				hvd3001c02v1UnlockA
				BitFail,
				hvd3001c02v1UnlockATrapEnable
				AlarmEnable,
				hvd3001c02v1LFailA
				BitFail,
				hvd3001c02v1LFailATrapEnable
				AlarmEnable,
				hvd3001c02v1HdA
				Bit0Sd1Hd,
				hvd3001c02v1NoElecA
				BitFail,
				hvd3001c02v1NoOpticA
				BitFail,
				hvd3001c02v1NoSigB
				BitFail,
				hvd3001c02v1NoSigBTrapEnable
				AlarmEnable,
				hvd3001c02v1UnlockB
				BitFail,
				hvd3001c02v1UnlockBTrapEnable
				AlarmEnable,
				hvd3001c02v1LFailB
				BitFail,
				hvd3001c02v1LFailBTrapEnable
				AlarmEnable,
				hvd3001c02v1HdB
				Bit0Sd1Hd,
				hvd3001c02v1NoElecB
				BitFail,
				hvd3001c02v1NoOpticB
				BitFail,
				hvd3001c02v1OpTxPres
				Bit0No1Yes,
				hvd3001c02v1OpRxPres
				Bit0No1Yes,
				hvd3001c02v1SfpTxSn
				SerialNo,
				hvd3001c02v1SfpRxSn
				SerialNo,
				hvd3001c02v1SerialNo
				SerialNo
			 }

		-- 1.3.6.1.4.1.10106.3.101291.1.1.1
		hvd3001c02v1Index OBJECT-TYPE
			SYNTAX ModuleIndex
			MAX-ACCESS read-only
			STATUS current
			DESCRIPTION
				"Index of HVD3001C02V1 Table"
		::= { hvd3001c02v1Entry 1 }

		-- 1.3.6.1.4.1.10106.3.101291.1.1.3
		hvd3001c02v1OpElecNA OBJECT-TYPE
			SYNTAX Bit0Ele1Opt
			MAX-ACCESS read-write
			STATUS current
			DESCRIPTION
				"Indicates the input selected"
		::= { hvd3001c02v1Entry 3 }

		-- 1.3.6.1.4.1.10106.3.101291.1.1.5
		hvd3001c02v1OpElecNB OBJECT-TYPE
			SYNTAX Bit0Ele1Opt
			MAX-ACCESS read-write
			STATUS current
			DESCRIPTION
				"Indicates the input selected"
		::= { hvd3001c02v1Entry 5 }

		-- 1.3.6.1.4.1.10106.3.101291.1.1.7
		hvd3001c02v1Mode OBJECT-TYPE
			SYNTAX BitDistrib1
			MAX-ACCESS read-write
			STATUS current
			DESCRIPTION
				"Operating mode"
		::= { hvd3001c02v1Entry 7 }

		-- 1.3.6.1.4.1.10106.3.101291.1.1.9
		hvd3001c02v1NoSigA OBJECT-TYPE
			SYNTAX BitFail
			MAX-ACCESS read-only
			STATUS current
			DESCRIPTION
				"Input signal status"
		::= { hvd3001c02v1Entry 9 }

		-- 1.3.6.1.4.1.10106.3.101291.1.1.10
		hvd3001c02v1NoSigATrapEnable OBJECT-TYPE
			SYNTAX AlarmEnable
			MAX-ACCESS read-write
			STATUS current
			DESCRIPTION
				"Input signal status Trap Enable"
		::= { hvd3001c02v1Entry 10 }

		-- 1.3.6.1.4.1.10106.3.101291.1.1.11
		hvd3001c02v1UnlockA OBJECT-TYPE
			SYNTAX BitFail
			MAX-ACCESS read-only
			STATUS current
			DESCRIPTION
				"Indicates signal unlock fail"
		::= { hvd3001c02v1Entry 11 }

		-- 1.3.6.1.4.1.10106.3.101291.1.1.12
		hvd3001c02v1UnlockATrapEnable OBJECT-TYPE
			SYNTAX AlarmEnable
			MAX-ACCESS read-write
			STATUS current
			DESCRIPTION
				"Indicates signal unlock fail Trap Enable"
		::= { hvd3001c02v1Entry 12 }

		-- 1.3.6.1.4.1.10106.3.101291.1.1.13
		hvd3001c02v1LFailA OBJECT-TYPE
			SYNTAX BitFail
			MAX-ACCESS read-only
			STATUS current
			DESCRIPTION
				"Indicates a fail in laser"
		::= { hvd3001c02v1Entry 13 }

		-- 1.3.6.1.4.1.10106.3.101291.1.1.14
		hvd3001c02v1LFailATrapEnable OBJECT-TYPE
			SYNTAX AlarmEnable
			MAX-ACCESS read-write
			STATUS current
			DESCRIPTION
				"Indicates a fail in laser Trap Enable"
		::= { hvd3001c02v1Entry 14 }

		-- 1.3.6.1.4.1.10106.3.101291.1.1.15
		hvd3001c02v1HdA OBJECT-TYPE
			SYNTAX Bit0Sd1Hd
			MAX-ACCESS read-only
			STATUS current
			DESCRIPTION
				"Indicates the SDI signal type"
		::= { hvd3001c02v1Entry 15 }

		-- 1.3.6.1.4.1.10106.3.101291.1.1.17
		hvd3001c02v1NoElecA OBJECT-TYPE
			SYNTAX BitFail
			MAX-ACCESS read-only
			STATUS current
			DESCRIPTION
				"Electrical input signal status"
		::= { hvd3001c02v1Entry 17 }

		-- 1.3.6.1.4.1.10106.3.101291.1.1.19
		hvd3001c02v1NoOpticA OBJECT-TYPE
			SYNTAX BitFail
			MAX-ACCESS read-only
			STATUS current
			DESCRIPTION
				"Optical input signal status"
		::= { hvd3001c02v1Entry 19 }

		-- 1.3.6.1.4.1.10106.3.101291.1.1.21
		hvd3001c02v1NoSigB OBJECT-TYPE
			SYNTAX BitFail
			MAX-ACCESS read-only
			STATUS current
			DESCRIPTION
				"Input signal status"
		::= { hvd3001c02v1Entry 21 }

		-- 1.3.6.1.4.1.10106.3.101291.1.1.22
		hvd3001c02v1NoSigBTrapEnable OBJECT-TYPE
			SYNTAX AlarmEnable
			MAX-ACCESS read-write
			STATUS current
			DESCRIPTION
				"Input signal status Trap Enable"
		::= { hvd3001c02v1Entry 22 }

		-- 1.3.6.1.4.1.10106.3.101291.1.1.23
		hvd3001c02v1UnlockB OBJECT-TYPE
			SYNTAX BitFail
			MAX-ACCESS read-only
			STATUS current
			DESCRIPTION
				"Indicates signal unlock fail"
		::= { hvd3001c02v1Entry 23 }

		-- 1.3.6.1.4.1.10106.3.101291.1.1.24
		hvd3001c02v1UnlockBTrapEnable OBJECT-TYPE
			SYNTAX AlarmEnable
			MAX-ACCESS read-write
			STATUS current
			DESCRIPTION
				"Indicates signal unlock fail Trap Enable"
		::= { hvd3001c02v1Entry 24 }

		-- 1.3.6.1.4.1.10106.3.101291.1.1.25
		hvd3001c02v1LFailB OBJECT-TYPE
			SYNTAX BitFail
			MAX-ACCESS read-only
			STATUS current
			DESCRIPTION
				"Indicates a fail in laser"
		::= { hvd3001c02v1Entry 25 }

		-- 1.3.6.1.4.1.10106.3.101291.1.1.26
		hvd3001c02v1LFailBTrapEnable OBJECT-TYPE
			SYNTAX AlarmEnable
			MAX-ACCESS read-write
			STATUS current
			DESCRIPTION
				"Indicates a fail in laser Trap Enable"
		::= { hvd3001c02v1Entry 26 }

		-- 1.3.6.1.4.1.10106.3.101291.1.1.27
		hvd3001c02v1HdB OBJECT-TYPE
			SYNTAX Bit0Sd1Hd
			MAX-ACCESS read-only
			STATUS current
			DESCRIPTION
				"Indicates the SDI signal type"
		::= { hvd3001c02v1Entry 27 }

		-- 1.3.6.1.4.1.10106.3.101291.1.1.29
		hvd3001c02v1NoElecB OBJECT-TYPE
			SYNTAX BitFail
			MAX-ACCESS read-only
			STATUS current
			DESCRIPTION
				"Electrical input signal status"
		::= { hvd3001c02v1Entry 29 }

		-- 1.3.6.1.4.1.10106.3.101291.1.1.31
		hvd3001c02v1NoOpticB OBJECT-TYPE
			SYNTAX BitFail
			MAX-ACCESS read-only
			STATUS current
			DESCRIPTION
				"Optical input signal status"
		::= { hvd3001c02v1Entry 31 }

		-- 1.3.6.1.4.1.10106.3.101291.1.1.33
		hvd3001c02v1OpTxPres OBJECT-TYPE
			SYNTAX Bit0No1Yes
			MAX-ACCESS read-only
			STATUS current
			DESCRIPTION
				"Indicates the presence of a SFP TX module"
		::= { hvd3001c02v1Entry 33 }

		-- 1.3.6.1.4.1.10106.3.101291.1.1.35
		hvd3001c02v1OpRxPres OBJECT-TYPE
			SYNTAX Bit0No1Yes
			MAX-ACCESS read-only
			STATUS current
			DESCRIPTION
				"Indicates the presence of a SFP RX module"
		::= { hvd3001c02v1Entry 35 }

		-- 1.3.6.1.4.1.10106.3.101291.1.1.37
		hvd3001c02v1SfpTxSn OBJECT-TYPE
			SYNTAX SerialNo
			MAX-ACCESS read-only
			STATUS current
			DESCRIPTION
				"SFP TX Serial number"
		::= { hvd3001c02v1Entry 37 }

		-- 1.3.6.1.4.1.10106.3.101291.1.1.39
		hvd3001c02v1SfpRxSn OBJECT-TYPE
			SYNTAX SerialNo
			MAX-ACCESS read-only
			STATUS current
			DESCRIPTION
				"SFP RX Serial number"
		::= { hvd3001c02v1Entry 39 }

		-- 1.3.6.1.4.1.10106.3.101291.1.1.41
		hvd3001c02v1SerialNo OBJECT-TYPE
			SYNTAX SerialNo
			MAX-ACCESS read-only
			STATUS current
			DESCRIPTION
				"Serial number"
		::= { hvd3001c02v1Entry 41 }

		-- 1.3.6.1.4.1.10106.3.357101
		hvd3001c03v1 OBJECT IDENTIFIER ::= { albalaProducts 357101 }

		-- 1.3.6.1.4.1.10106.3.357101.1
		hvd3001c03v1Table  OBJECT-TYPE
			SYNTAX SEQUENCE OF Hvd3001c03v1Entry
			MAX-ACCESS not-accessible
			STATUS current
			DESCRIPTION
				"Module  HVD3001C03V1 Table"
			::= { hvd3001c03v1 1 }

		-- 1.3.6.1.4.1.10106.3.357101.1.1
		hvd3001c03v1Entry  OBJECT-TYPE
			SYNTAX Hvd3001c03v1Entry
			MAX-ACCESS not-accessible
			STATUS current
			DESCRIPTION
				"Module HVD3001C03V1 Entry"
			INDEX { hvd3001c03v1Index }
			::= { hvd3001c03v1Table 1 }

			Hvd3001c03v1Entry ::=
			SEQUENCE {
				hvd3001c03v1Index
				ModuleIndex,
				hvd3001c03v1OpElecNA
				Bit0Ele1Opt,
				hvd3001c03v1OpElecNB
				Bit0Ele1Opt,
				hvd3001c03v1Mode
				BitDistrib1,
				hvd3001c03v1NoSigA
				BitFail,
				hvd3001c03v1NoSigATrapEnable
				AlarmEnable,
				hvd3001c03v1UnlockA
				BitFail,
				hvd3001c03v1UnlockATrapEnable
				AlarmEnable,
				hvd3001c03v1LFailA
				BitFail,
				hvd3001c03v1LFailATrapEnable
				AlarmEnable,
				hvd3001c03v1HdA
				Bit0Sd1Hd,
				hvd3001c03v1NoElecA
				BitFail,
				hvd3001c03v1NoOpticA
				BitFail,
				hvd3001c03v1NoSigB
				BitFail,
				hvd3001c03v1NoSigBTrapEnable
				AlarmEnable,
				hvd3001c03v1UnlockB
				BitFail,
				hvd3001c03v1UnlockBTrapEnable
				AlarmEnable,
				hvd3001c03v1LFailB
				BitFail,
				hvd3001c03v1LFailBTrapEnable
				AlarmEnable,
				hvd3001c03v1HdB
				Bit0Sd1Hd,
				hvd3001c03v1NoElecB
				BitFail,
				hvd3001c03v1NoOpticB
				BitFail,
				hvd3001c03v1OpTxPres
				Bit0No1Yes,
				hvd3001c03v1OpRxPres
				Bit0No1Yes,
				hvd3001c03v1SfpTxSn
				SerialNo,
				hvd3001c03v1SfpRxSn
				SerialNo,
				hvd3001c03v1SerialNo
				SerialNo
			 }

		-- 1.3.6.1.4.1.10106.3.101291.1.1.1
		hvd3001c03v1Index OBJECT-TYPE
			SYNTAX ModuleIndex
			MAX-ACCESS read-only
			STATUS current
			DESCRIPTION
				"Index of HVD3001C03V1 Table"
		::= { hvd3001c03v1Entry 1 }

		-- 1.3.6.1.4.1.10106.3.101291.1.1.3
		hvd3001c03v1OpElecNA OBJECT-TYPE
			SYNTAX Bit0Ele1Opt
			MAX-ACCESS read-write
			STATUS current
			DESCRIPTION
				"Indicates the input selected"
		::= { hvd3001c03v1Entry 3 }

		-- 1.3.6.1.4.1.10106.3.101291.1.1.5
		hvd3001c03v1OpElecNB OBJECT-TYPE
			SYNTAX Bit0Ele1Opt
			MAX-ACCESS read-write
			STATUS current
			DESCRIPTION
				"Indicates the input selected"
		::= { hvd3001c03v1Entry 5 }

		-- 1.3.6.1.4.1.10106.3.101291.1.1.7
		hvd3001c03v1Mode OBJECT-TYPE
			SYNTAX BitDistrib1
			MAX-ACCESS read-write
			STATUS current
			DESCRIPTION
				"Operating mode"
		::= { hvd3001c03v1Entry 7 }

		-- 1.3.6.1.4.1.10106.3.101291.1.1.9
		hvd3001c03v1NoSigA OBJECT-TYPE
			SYNTAX BitFail
			MAX-ACCESS read-only
			STATUS current
			DESCRIPTION
				"Input signal status"
		::= { hvd3001c03v1Entry 9 }

		-- 1.3.6.1.4.1.10106.3.101291.1.1.10
		hvd3001c03v1NoSigATrapEnable OBJECT-TYPE
			SYNTAX AlarmEnable
			MAX-ACCESS read-write
			STATUS current
			DESCRIPTION
				"Input signal status Trap Enable"
		::= { hvd3001c03v1Entry 10 }

		-- 1.3.6.1.4.1.10106.3.101291.1.1.11
		hvd3001c03v1UnlockA OBJECT-TYPE
			SYNTAX BitFail
			MAX-ACCESS read-only
			STATUS current
			DESCRIPTION
				"Indicates signal unlock fail"
		::= { hvd3001c03v1Entry 11 }

		-- 1.3.6.1.4.1.10106.3.101291.1.1.12
		hvd3001c03v1UnlockATrapEnable OBJECT-TYPE
			SYNTAX AlarmEnable
			MAX-ACCESS read-write
			STATUS current
			DESCRIPTION
				"Indicates signal unlock fail Trap Enable"
		::= { hvd3001c03v1Entry 12 }

		-- 1.3.6.1.4.1.10106.3.101291.1.1.13
		hvd3001c03v1LFailA OBJECT-TYPE
			SYNTAX BitFail
			MAX-ACCESS read-only
			STATUS current
			DESCRIPTION
				"Indicates a fail in laser"
		::= { hvd3001c03v1Entry 13 }

		-- 1.3.6.1.4.1.10106.3.101291.1.1.14
		hvd3001c03v1LFailATrapEnable OBJECT-TYPE
			SYNTAX AlarmEnable
			MAX-ACCESS read-write
			STATUS current
			DESCRIPTION
				"Indicates a fail in laser Trap Enable"
		::= { hvd3001c03v1Entry 14 }

		-- 1.3.6.1.4.1.10106.3.101291.1.1.15
		hvd3001c03v1HdA OBJECT-TYPE
			SYNTAX Bit0Sd1Hd
			MAX-ACCESS read-only
			STATUS current
			DESCRIPTION
				"Indicates the SDI signal type"
		::= { hvd3001c03v1Entry 15 }

		-- 1.3.6.1.4.1.10106.3.101291.1.1.17
		hvd3001c03v1NoElecA OBJECT-TYPE
			SYNTAX BitFail
			MAX-ACCESS read-only
			STATUS current
			DESCRIPTION
				"Electrical input signal status"
		::= { hvd3001c03v1Entry 17 }

		-- 1.3.6.1.4.1.10106.3.101291.1.1.19
		hvd3001c03v1NoOpticA OBJECT-TYPE
			SYNTAX BitFail
			MAX-ACCESS read-only
			STATUS current
			DESCRIPTION
				"Optical input signal status"
		::= { hvd3001c03v1Entry 19 }

		-- 1.3.6.1.4.1.10106.3.101291.1.1.21
		hvd3001c03v1NoSigB OBJECT-TYPE
			SYNTAX BitFail
			MAX-ACCESS read-only
			STATUS current
			DESCRIPTION
				"Input signal status"
		::= { hvd3001c03v1Entry 21 }

		-- 1.3.6.1.4.1.10106.3.101291.1.1.22
		hvd3001c03v1NoSigBTrapEnable OBJECT-TYPE
			SYNTAX AlarmEnable
			MAX-ACCESS read-write
			STATUS current
			DESCRIPTION
				"Input signal status Trap Enable"
		::= { hvd3001c03v1Entry 22 }

		-- 1.3.6.1.4.1.10106.3.101291.1.1.23
		hvd3001c03v1UnlockB OBJECT-TYPE
			SYNTAX BitFail
			MAX-ACCESS read-only
			STATUS current
			DESCRIPTION
				"Indicates signal unlock fail"
		::= { hvd3001c03v1Entry 23 }

		-- 1.3.6.1.4.1.10106.3.101291.1.1.24
		hvd3001c03v1UnlockBTrapEnable OBJECT-TYPE
			SYNTAX AlarmEnable
			MAX-ACCESS read-write
			STATUS current
			DESCRIPTION
				"Indicates signal unlock fail Trap Enable"
		::= { hvd3001c03v1Entry 24 }

		-- 1.3.6.1.4.1.10106.3.101291.1.1.25
		hvd3001c03v1LFailB OBJECT-TYPE
			SYNTAX BitFail
			MAX-ACCESS read-only
			STATUS current
			DESCRIPTION
				"Indicates a fail in laser"
		::= { hvd3001c03v1Entry 25 }

		-- 1.3.6.1.4.1.10106.3.101291.1.1.26
		hvd3001c03v1LFailBTrapEnable OBJECT-TYPE
			SYNTAX AlarmEnable
			MAX-ACCESS read-write
			STATUS current
			DESCRIPTION
				"Indicates a fail in laser Trap Enable"
		::= { hvd3001c03v1Entry 26 }

		-- 1.3.6.1.4.1.10106.3.101291.1.1.27
		hvd3001c03v1HdB OBJECT-TYPE
			SYNTAX Bit0Sd1Hd
			MAX-ACCESS read-only
			STATUS current
			DESCRIPTION
				"Indicates the SDI signal type"
		::= { hvd3001c03v1Entry 27 }

		-- 1.3.6.1.4.1.10106.3.101291.1.1.29
		hvd3001c03v1NoElecB OBJECT-TYPE
			SYNTAX BitFail
			MAX-ACCESS read-only
			STATUS current
			DESCRIPTION
				"Electrical input signal status"
		::= { hvd3001c03v1Entry 29 }

		-- 1.3.6.1.4.1.10106.3.101291.1.1.31
		hvd3001c03v1NoOpticB OBJECT-TYPE
			SYNTAX BitFail
			MAX-ACCESS read-only
			STATUS current
			DESCRIPTION
				"Optical input signal status"
		::= { hvd3001c03v1Entry 31 }

		-- 1.3.6.1.4.1.10106.3.101291.1.1.33
		hvd3001c03v1OpTxPres OBJECT-TYPE
			SYNTAX Bit0No1Yes
			MAX-ACCESS read-only
			STATUS current
			DESCRIPTION
				"Indicates the presence of a SFP TX module"
		::= { hvd3001c03v1Entry 33 }

		-- 1.3.6.1.4.1.10106.3.101291.1.1.35
		hvd3001c03v1OpRxPres OBJECT-TYPE
			SYNTAX Bit0No1Yes
			MAX-ACCESS read-only
			STATUS current
			DESCRIPTION
				"Indicates the presence of a SFP RX module"
		::= { hvd3001c03v1Entry 35 }

		-- 1.3.6.1.4.1.10106.3.101291.1.1.37
		hvd3001c03v1SfpTxSn OBJECT-TYPE
			SYNTAX SerialNo
			MAX-ACCESS read-only
			STATUS current
			DESCRIPTION
				"SFP TX Serial number"
		::= { hvd3001c03v1Entry 37 }

		-- 1.3.6.1.4.1.10106.3.101291.1.1.39
		hvd3001c03v1SfpRxSn OBJECT-TYPE
			SYNTAX SerialNo
			MAX-ACCESS read-only
			STATUS current
			DESCRIPTION
				"SFP RX Serial number"
		::= { hvd3001c03v1Entry 39 }

		-- 1.3.6.1.4.1.10106.3.101291.1.1.41
		hvd3001c03v1SerialNo OBJECT-TYPE
			SYNTAX SerialNo
			MAX-ACCESS read-only
			STATUS current
			DESCRIPTION
				"Serial number"
		::= { hvd3001c03v1Entry 41 }

		-- 1.3.6.1.4.1.10106.3.357201
		hvd3001c04v1 OBJECT IDENTIFIER ::= { albalaProducts 357201 }

		-- 1.3.6.1.4.1.10106.3.357201.1
		hvd3001c04v1Table  OBJECT-TYPE
			SYNTAX SEQUENCE OF Hvd3001c04v1Entry
			MAX-ACCESS not-accessible
			STATUS current
			DESCRIPTION
				"Module  HVD3001C04V1 Table"
			::= { hvd3001c04v1 1 }

		-- 1.3.6.1.4.1.10106.3.357201.1.1
		hvd3001c04v1Entry  OBJECT-TYPE
			SYNTAX Hvd3001c04v1Entry
			MAX-ACCESS not-accessible
			STATUS current
			DESCRIPTION
				"Module HVD3001C04V1 Entry"
			INDEX { hvd3001c04v1Index }
			::= { hvd3001c04v1Table 1 }

			Hvd3001c04v1Entry ::=
			SEQUENCE {
				hvd3001c04v1Index
				ModuleIndex,
				hvd3001c04v1OpElecNA
				Bit0Ele1Opt,
				hvd3001c04v1OpElecNB
				Bit0Ele1Opt,
				hvd3001c04v1Mode
				BitDistrib1,
				hvd3001c04v1NoSigA
				BitFail,
				hvd3001c04v1NoSigATrapEnable
				AlarmEnable,
				hvd3001c04v1UnlockA
				BitFail,
				hvd3001c04v1UnlockATrapEnable
				AlarmEnable,
				hvd3001c04v1LFailA
				BitFail,
				hvd3001c04v1LFailATrapEnable
				AlarmEnable,
				hvd3001c04v1HdA
				Bit0Sd1Hd,
				hvd3001c04v1NoElecA
				BitFail,
				hvd3001c04v1NoOpticA
				BitFail,
				hvd3001c04v1NoSigB
				BitFail,
				hvd3001c04v1NoSigBTrapEnable
				AlarmEnable,
				hvd3001c04v1UnlockB
				BitFail,
				hvd3001c04v1UnlockBTrapEnable
				AlarmEnable,
				hvd3001c04v1LFailB
				BitFail,
				hvd3001c04v1LFailBTrapEnable
				AlarmEnable,
				hvd3001c04v1HdB
				Bit0Sd1Hd,
				hvd3001c04v1NoElecB
				BitFail,
				hvd3001c04v1NoOpticB
				BitFail,
				hvd3001c04v1OpTxPres
				Bit0No1Yes,
				hvd3001c04v1OpRxPres
				Bit0No1Yes,
				hvd3001c04v1SfpTxSn
				SerialNo,
				hvd3001c04v1SfpRxSn
				SerialNo,
				hvd3001c04v1SerialNo
				SerialNo
			 }

		-- 1.3.6.1.4.1.10106.3.101291.1.1.1
		hvd3001c04v1Index OBJECT-TYPE
			SYNTAX ModuleIndex
			MAX-ACCESS read-only
			STATUS current
			DESCRIPTION
				"Index of HVD3001C04V1 Table"
		::= { hvd3001c04v1Entry 1 }

		-- 1.3.6.1.4.1.10106.3.101291.1.1.3
		hvd3001c04v1OpElecNA OBJECT-TYPE
			SYNTAX Bit0Ele1Opt
			MAX-ACCESS read-write
			STATUS current
			DESCRIPTION
				"Indicates the input selected"
		::= { hvd3001c04v1Entry 3 }

		-- 1.3.6.1.4.1.10106.3.101291.1.1.5
		hvd3001c04v1OpElecNB OBJECT-TYPE
			SYNTAX Bit0Ele1Opt
			MAX-ACCESS read-write
			STATUS current
			DESCRIPTION
				"Indicates the input selected"
		::= { hvd3001c04v1Entry 5 }

		-- 1.3.6.1.4.1.10106.3.101291.1.1.7
		hvd3001c04v1Mode OBJECT-TYPE
			SYNTAX BitDistrib1
			MAX-ACCESS read-write
			STATUS current
			DESCRIPTION
				"Operating mode"
		::= { hvd3001c04v1Entry 7 }

		-- 1.3.6.1.4.1.10106.3.101291.1.1.9
		hvd3001c04v1NoSigA OBJECT-TYPE
			SYNTAX BitFail
			MAX-ACCESS read-only
			STATUS current
			DESCRIPTION
				"Input signal status"
		::= { hvd3001c04v1Entry 9 }

		-- 1.3.6.1.4.1.10106.3.101291.1.1.10
		hvd3001c04v1NoSigATrapEnable OBJECT-TYPE
			SYNTAX AlarmEnable
			MAX-ACCESS read-write
			STATUS current
			DESCRIPTION
				"Input signal status Trap Enable"
		::= { hvd3001c04v1Entry 10 }

		-- 1.3.6.1.4.1.10106.3.101291.1.1.11
		hvd3001c04v1UnlockA OBJECT-TYPE
			SYNTAX BitFail
			MAX-ACCESS read-only
			STATUS current
			DESCRIPTION
				"Indicates signal unlock fail"
		::= { hvd3001c04v1Entry 11 }

		-- 1.3.6.1.4.1.10106.3.101291.1.1.12
		hvd3001c04v1UnlockATrapEnable OBJECT-TYPE
			SYNTAX AlarmEnable
			MAX-ACCESS read-write
			STATUS current
			DESCRIPTION
				"Indicates signal unlock fail Trap Enable"
		::= { hvd3001c04v1Entry 12 }

		-- 1.3.6.1.4.1.10106.3.101291.1.1.13
		hvd3001c04v1LFailA OBJECT-TYPE
			SYNTAX BitFail
			MAX-ACCESS read-only
			STATUS current
			DESCRIPTION
				"Indicates a fail in laser"
		::= { hvd3001c04v1Entry 13 }

		-- 1.3.6.1.4.1.10106.3.101291.1.1.14
		hvd3001c04v1LFailATrapEnable OBJECT-TYPE
			SYNTAX AlarmEnable
			MAX-ACCESS read-write
			STATUS current
			DESCRIPTION
				"Indicates a fail in laser Trap Enable"
		::= { hvd3001c04v1Entry 14 }

		-- 1.3.6.1.4.1.10106.3.101291.1.1.15
		hvd3001c04v1HdA OBJECT-TYPE
			SYNTAX Bit0Sd1Hd
			MAX-ACCESS read-only
			STATUS current
			DESCRIPTION
				"Indicates the SDI signal type"
		::= { hvd3001c04v1Entry 15 }

		-- 1.3.6.1.4.1.10106.3.101291.1.1.17
		hvd3001c04v1NoElecA OBJECT-TYPE
			SYNTAX BitFail
			MAX-ACCESS read-only
			STATUS current
			DESCRIPTION
				"Electrical input signal status"
		::= { hvd3001c04v1Entry 17 }

		-- 1.3.6.1.4.1.10106.3.101291.1.1.19
		hvd3001c04v1NoOpticA OBJECT-TYPE
			SYNTAX BitFail
			MAX-ACCESS read-only
			STATUS current
			DESCRIPTION
				"Optical input signal status"
		::= { hvd3001c04v1Entry 19 }

		-- 1.3.6.1.4.1.10106.3.101291.1.1.21
		hvd3001c04v1NoSigB OBJECT-TYPE
			SYNTAX BitFail
			MAX-ACCESS read-only
			STATUS current
			DESCRIPTION
				"Input signal status"
		::= { hvd3001c04v1Entry 21 }

		-- 1.3.6.1.4.1.10106.3.101291.1.1.22
		hvd3001c04v1NoSigBTrapEnable OBJECT-TYPE
			SYNTAX AlarmEnable
			MAX-ACCESS read-write
			STATUS current
			DESCRIPTION
				"Input signal status Trap Enable"
		::= { hvd3001c04v1Entry 22 }

		-- 1.3.6.1.4.1.10106.3.101291.1.1.23
		hvd3001c04v1UnlockB OBJECT-TYPE
			SYNTAX BitFail
			MAX-ACCESS read-only
			STATUS current
			DESCRIPTION
				"Indicates signal unlock fail"
		::= { hvd3001c04v1Entry 23 }

		-- 1.3.6.1.4.1.10106.3.101291.1.1.24
		hvd3001c04v1UnlockBTrapEnable OBJECT-TYPE
			SYNTAX AlarmEnable
			MAX-ACCESS read-write
			STATUS current
			DESCRIPTION
				"Indicates signal unlock fail Trap Enable"
		::= { hvd3001c04v1Entry 24 }

		-- 1.3.6.1.4.1.10106.3.101291.1.1.25
		hvd3001c04v1LFailB OBJECT-TYPE
			SYNTAX BitFail
			MAX-ACCESS read-only
			STATUS current
			DESCRIPTION
				"Indicates a fail in laser"
		::= { hvd3001c04v1Entry 25 }

		-- 1.3.6.1.4.1.10106.3.101291.1.1.26
		hvd3001c04v1LFailBTrapEnable OBJECT-TYPE
			SYNTAX AlarmEnable
			MAX-ACCESS read-write
			STATUS current
			DESCRIPTION
				"Indicates a fail in laser Trap Enable"
		::= { hvd3001c04v1Entry 26 }

		-- 1.3.6.1.4.1.10106.3.101291.1.1.27
		hvd3001c04v1HdB OBJECT-TYPE
			SYNTAX Bit0Sd1Hd
			MAX-ACCESS read-only
			STATUS current
			DESCRIPTION
				"Indicates the SDI signal type"
		::= { hvd3001c04v1Entry 27 }

		-- 1.3.6.1.4.1.10106.3.101291.1.1.29
		hvd3001c04v1NoElecB OBJECT-TYPE
			SYNTAX BitFail
			MAX-ACCESS read-only
			STATUS current
			DESCRIPTION
				"Electrical input signal status"
		::= { hvd3001c04v1Entry 29 }

		-- 1.3.6.1.4.1.10106.3.101291.1.1.31
		hvd3001c04v1NoOpticB OBJECT-TYPE
			SYNTAX BitFail
			MAX-ACCESS read-only
			STATUS current
			DESCRIPTION
				"Optical input signal status"
		::= { hvd3001c04v1Entry 31 }

		-- 1.3.6.1.4.1.10106.3.101291.1.1.33
		hvd3001c04v1OpTxPres OBJECT-TYPE
			SYNTAX Bit0No1Yes
			MAX-ACCESS read-only
			STATUS current
			DESCRIPTION
				"Indicates the presence of a SFP TX module"
		::= { hvd3001c04v1Entry 33 }

		-- 1.3.6.1.4.1.10106.3.101291.1.1.35
		hvd3001c04v1OpRxPres OBJECT-TYPE
			SYNTAX Bit0No1Yes
			MAX-ACCESS read-only
			STATUS current
			DESCRIPTION
				"Indicates the presence of a SFP RX module"
		::= { hvd3001c04v1Entry 35 }

		-- 1.3.6.1.4.1.10106.3.101291.1.1.37
		hvd3001c04v1SfpTxSn OBJECT-TYPE
			SYNTAX SerialNo
			MAX-ACCESS read-only
			STATUS current
			DESCRIPTION
				"SFP TX Serial number"
		::= { hvd3001c04v1Entry 37 }

		-- 1.3.6.1.4.1.10106.3.101291.1.1.39
		hvd3001c04v1SfpRxSn OBJECT-TYPE
			SYNTAX SerialNo
			MAX-ACCESS read-only
			STATUS current
			DESCRIPTION
				"SFP RX Serial number"
		::= { hvd3001c04v1Entry 39 }

		-- 1.3.6.1.4.1.10106.3.101291.1.1.41
		hvd3001c04v1SerialNo OBJECT-TYPE
			SYNTAX SerialNo
			MAX-ACCESS read-only
			STATUS current
			DESCRIPTION
				"Serial number"
		::= { hvd3001c04v1Entry 41 }

		-- 1.3.6.1.4.1.10106.3.357501
		hfs3000c01v1 OBJECT IDENTIFIER ::= { albalaProducts 357501 }

		-- 1.3.6.1.4.1.10106.3.357501.1
		hfs3000c01v1Table  OBJECT-TYPE
			SYNTAX SEQUENCE OF Hfs3000c01v1Entry
			MAX-ACCESS not-accessible
			STATUS current
			DESCRIPTION
				"Module  HFS3000C01V1 Table"
			::= { hfs3000c01v1 1 }

		-- 1.3.6.1.4.1.10106.3.357501.1.1
		hfs3000c01v1Entry  OBJECT-TYPE
			SYNTAX Hfs3000c01v1Entry
			MAX-ACCESS not-accessible
			STATUS current
			DESCRIPTION
				"Module HFS3000C01V1 Entry"
			INDEX { hfs3000c01v1Index }
			::= { hfs3000c01v1Table 1 }

			Hfs3000c01v1Entry ::=
			SEQUENCE {
				hfs3000c01v1Index
				ModuleIndex,
				hfs3000c01v1SynchroModeA
				Bit0Fra1Lin,
				hfs3000c01v1FailModeA
				Bit0Fre1Blk,
				hfs3000c01v1VbiModeA
				Bit0Pas1Bnk,
				hfs3000c01v1DelayModeA
				Bit0Syn1De2,
				hfs3000c01v1SynchroModeB
				Bit0Fra1Lin,
				hfs3000c01v1FailModeB
				Bit0Fre1Blk,
				hfs3000c01v1VbiModeB
				Bit0Pas1Bnk,
				hfs3000c01v1DelayModeB
				Bit0Syn1De2,
				hfs3000c01v1HDelayA
				DelayPixel5,
				hfs3000c01v1FrameDelayA
				DelayFram4,
				hfs3000c01v1VDelayA
				DelayLines2,
				hfs3000c01v1LumaGainA
				GainLin1,
				hfs3000c01v1ChromaGainA
				GainLin1,
				hfs3000c01v1BlackOffsetA
				BlackOffset1,
				hfs3000c01v1HDelayB
				DelayPixel5,
				hfs3000c01v1FrameDelayB
				DelayFram4,
				hfs3000c01v1VDelayB
				DelayLines2,
				hfs3000c01v1LumaGainB
				GainLin1,
				hfs3000c01v1ChromaGainB
				GainLin1,
				hfs3000c01v1BlackOffsetB
				BlackOffset1,
				hfs3000c01v1NoSigA
				BitFail,
				hfs3000c01v1NoSigATrapEnable
				AlarmEnable,
				hfs3000c01v1UnlockA
				BitFail,
				hfs3000c01v1UnlockATrapEnable
				AlarmEnable,
				hfs3000c01v1EdhCrcA
				BitFail,
				hfs3000c01v1EdhCrcATrapEnable
				AlarmEnable,
				hfs3000c01v1GpiFailA
				BitFail,
				hfs3000c01v1GpiFailATrapEnable
				AlarmEnable,
				hfs3000c01v1NoSigB
				BitFail,
				hfs3000c01v1NoSigBTrapEnable
				AlarmEnable,
				hfs3000c01v1UnlockB
				BitFail,
				hfs3000c01v1UnlockBTrapEnable
				AlarmEnable,
				hfs3000c01v1EdhCrcB
				BitFail,
				hfs3000c01v1EdhCrcBTrapEnable
				AlarmEnable,
				hfs3000c01v1GpiFailB
				BitFail,
				hfs3000c01v1GpiFailBTrapEnable
				AlarmEnable,
				hfs3000c01v1NoRef
				BitFail,
				hfs3000c01v1NoRefTrapEnable
				AlarmEnable,
				hfs3000c01v1RefAUnlock
				BitFail,
				hfs3000c01v1RefAUnlockTrapEnable
				AlarmEnable,
				hfs3000c01v1RefBUnlock
				BitFail,
				hfs3000c01v1RefBUnlockTrapEnable
				AlarmEnable,
				hfs3000c01v1InputFormat
				SdiHd3gFmt3,
				hfs3000c01v1SdiFormatA
				SdiHd3gFmt3,
				hfs3000c01v1SdiFormatB
				SdiHd3gFmt3,
				hfs3000c01v1SigDelayA
				DelayX20Us,
				hfs3000c01v1SigDelayB
				DelayX20Us,
				hfs3000c01v1SerialNo
				SerialNo
			 }

		-- 1.3.6.1.4.1.10106.3.101291.1.1.1
		hfs3000c01v1Index OBJECT-TYPE
			SYNTAX ModuleIndex
			MAX-ACCESS read-only
			STATUS current
			DESCRIPTION
				"Index of HFS3000C01V1 Table"
		::= { hfs3000c01v1Entry 1 }

		-- 1.3.6.1.4.1.10106.3.101291.1.1.3
		hfs3000c01v1SynchroModeA OBJECT-TYPE
			SYNTAX Bit0Fra1Lin
			MAX-ACCESS read-write
			STATUS current
			DESCRIPTION
				"Allows selecting the synchronizing mode"
		::= { hfs3000c01v1Entry 3 }

		-- 1.3.6.1.4.1.10106.3.101291.1.1.5
		hfs3000c01v1FailModeA OBJECT-TYPE
			SYNTAX Bit0Fre1Blk
			MAX-ACCESS read-write
			STATUS current
			DESCRIPTION
				"Allows selecting the output video signal if the input fails"
		::= { hfs3000c01v1Entry 5 }

		-- 1.3.6.1.4.1.10106.3.101291.1.1.7
		hfs3000c01v1VbiModeA OBJECT-TYPE
			SYNTAX Bit0Pas1Bnk
			MAX-ACCESS read-write
			STATUS current
			DESCRIPTION
				"Allows selecting if the VBI is blanked"
		::= { hfs3000c01v1Entry 7 }

		-- 1.3.6.1.4.1.10106.3.101291.1.1.9
		hfs3000c01v1DelayModeA OBJECT-TYPE
			SYNTAX Bit0Syn1De2
			MAX-ACCESS read-write
			STATUS current
			DESCRIPTION
				"Allows selecting the operating mode"
		::= { hfs3000c01v1Entry 9 }

		-- 1.3.6.1.4.1.10106.3.101291.1.1.11
		hfs3000c01v1SynchroModeB OBJECT-TYPE
			SYNTAX Bit0Fra1Lin
			MAX-ACCESS read-write
			STATUS current
			DESCRIPTION
				"Allows selecting the synchronizing mode"
		::= { hfs3000c01v1Entry 11 }

		-- 1.3.6.1.4.1.10106.3.101291.1.1.13
		hfs3000c01v1FailModeB OBJECT-TYPE
			SYNTAX Bit0Fre1Blk
			MAX-ACCESS read-write
			STATUS current
			DESCRIPTION
				"Allows selecting the output video signal if the input fails"
		::= { hfs3000c01v1Entry 13 }

		-- 1.3.6.1.4.1.10106.3.101291.1.1.15
		hfs3000c01v1VbiModeB OBJECT-TYPE
			SYNTAX Bit0Pas1Bnk
			MAX-ACCESS read-write
			STATUS current
			DESCRIPTION
				"Allows selecting if the VBI is blanked"
		::= { hfs3000c01v1Entry 15 }

		-- 1.3.6.1.4.1.10106.3.101291.1.1.17
		hfs3000c01v1DelayModeB OBJECT-TYPE
			SYNTAX Bit0Syn1De2
			MAX-ACCESS read-write
			STATUS current
			DESCRIPTION
				"Allows selecting the operating mode"
		::= { hfs3000c01v1Entry 17 }

		-- 1.3.6.1.4.1.10106.3.101291.1.1.19
		hfs3000c01v1HDelayA OBJECT-TYPE
			SYNTAX DelayPixel5
			MAX-ACCESS read-write
			STATUS current
			DESCRIPTION
				"Allows adjusting the video horizontal delay"
		::= { hfs3000c01v1Entry 19 }

		-- 1.3.6.1.4.1.10106.3.101291.1.1.21
		hfs3000c01v1FrameDelayA OBJECT-TYPE
			SYNTAX DelayFram4
			MAX-ACCESS read-write
			STATUS current
			DESCRIPTION
				"Allows adjusting the frame delay"
		::= { hfs3000c01v1Entry 21 }

		-- 1.3.6.1.4.1.10106.3.101291.1.1.23
		hfs3000c01v1VDelayA OBJECT-TYPE
			SYNTAX DelayLines2
			MAX-ACCESS read-write
			STATUS current
			DESCRIPTION
				"Allows adjusting the video vertical delay"
		::= { hfs3000c01v1Entry 23 }

		-- 1.3.6.1.4.1.10106.3.101291.1.1.25
		hfs3000c01v1LumaGainA OBJECT-TYPE
			SYNTAX GainLin1
			MAX-ACCESS read-write
			STATUS current
			DESCRIPTION
				"Allows adjusting the luma gain"
		::= { hfs3000c01v1Entry 25 }

		-- 1.3.6.1.4.1.10106.3.101291.1.1.27
		hfs3000c01v1ChromaGainA OBJECT-TYPE
			SYNTAX GainLin1
			MAX-ACCESS read-write
			STATUS current
			DESCRIPTION
				"Allows adjusting the chorma gain"
		::= { hfs3000c01v1Entry 27 }

		-- 1.3.6.1.4.1.10106.3.101291.1.1.29
		hfs3000c01v1BlackOffsetA OBJECT-TYPE
			SYNTAX BlackOffset1
			MAX-ACCESS read-write
			STATUS current
			DESCRIPTION
				"Allows adjusting the black offset"
		::= { hfs3000c01v1Entry 29 }

		-- 1.3.6.1.4.1.10106.3.101291.1.1.31
		hfs3000c01v1HDelayB OBJECT-TYPE
			SYNTAX DelayPixel5
			MAX-ACCESS read-write
			STATUS current
			DESCRIPTION
				"Allows adjusting the video horizontal delay"
		::= { hfs3000c01v1Entry 31 }

		-- 1.3.6.1.4.1.10106.3.101291.1.1.33
		hfs3000c01v1FrameDelayB OBJECT-TYPE
			SYNTAX DelayFram4
			MAX-ACCESS read-write
			STATUS current
			DESCRIPTION
				"Allows adjusting the frame delay"
		::= { hfs3000c01v1Entry 33 }

		-- 1.3.6.1.4.1.10106.3.101291.1.1.35
		hfs3000c01v1VDelayB OBJECT-TYPE
			SYNTAX DelayLines2
			MAX-ACCESS read-write
			STATUS current
			DESCRIPTION
				"Allows adjusting the video vertical delay"
		::= { hfs3000c01v1Entry 35 }

		-- 1.3.6.1.4.1.10106.3.101291.1.1.37
		hfs3000c01v1LumaGainB OBJECT-TYPE
			SYNTAX GainLin1
			MAX-ACCESS read-write
			STATUS current
			DESCRIPTION
				"Allows adjusting the luma gain"
		::= { hfs3000c01v1Entry 37 }

		-- 1.3.6.1.4.1.10106.3.101291.1.1.39
		hfs3000c01v1ChromaGainB OBJECT-TYPE
			SYNTAX GainLin1
			MAX-ACCESS read-write
			STATUS current
			DESCRIPTION
				"Allows adjusting the chorma gain"
		::= { hfs3000c01v1Entry 39 }

		-- 1.3.6.1.4.1.10106.3.101291.1.1.41
		hfs3000c01v1BlackOffsetB OBJECT-TYPE
			SYNTAX BlackOffset1
			MAX-ACCESS read-write
			STATUS current
			DESCRIPTION
				"Allows adjusting the black offset"
		::= { hfs3000c01v1Entry 41 }

		-- 1.3.6.1.4.1.10106.3.101291.1.1.43
		hfs3000c01v1NoSigA OBJECT-TYPE
			SYNTAX BitFail
			MAX-ACCESS read-only
			STATUS current
			DESCRIPTION
				"Indicates SDI signal fail"
		::= { hfs3000c01v1Entry 43 }

		-- 1.3.6.1.4.1.10106.3.101291.1.1.44
		hfs3000c01v1NoSigATrapEnable OBJECT-TYPE
			SYNTAX AlarmEnable
			MAX-ACCESS read-write
			STATUS current
			DESCRIPTION
				"Indicates SDI signal fail Trap Enable"
		::= { hfs3000c01v1Entry 44 }

		-- 1.3.6.1.4.1.10106.3.101291.1.1.45
		hfs3000c01v1UnlockA OBJECT-TYPE
			SYNTAX BitFail
			MAX-ACCESS read-only
			STATUS current
			DESCRIPTION
				"Indicates signal unlock"
		::= { hfs3000c01v1Entry 45 }

		-- 1.3.6.1.4.1.10106.3.101291.1.1.46
		hfs3000c01v1UnlockATrapEnable OBJECT-TYPE
			SYNTAX AlarmEnable
			MAX-ACCESS read-write
			STATUS current
			DESCRIPTION
				"Indicates signal unlock Trap Enable"
		::= { hfs3000c01v1Entry 46 }

		-- 1.3.6.1.4.1.10106.3.101291.1.1.47
		hfs3000c01v1EdhCrcA OBJECT-TYPE
			SYNTAX BitFail
			MAX-ACCESS read-only
			STATUS current
			DESCRIPTION
				"Indicates presence of EDH/CRC errors"
		::= { hfs3000c01v1Entry 47 }

		-- 1.3.6.1.4.1.10106.3.101291.1.1.48
		hfs3000c01v1EdhCrcATrapEnable OBJECT-TYPE
			SYNTAX AlarmEnable
			MAX-ACCESS read-write
			STATUS current
			DESCRIPTION
				"Indicates presence of EDH/CRC errors Trap Enable"
		::= { hfs3000c01v1Entry 48 }

		-- 1.3.6.1.4.1.10106.3.101291.1.1.49
		hfs3000c01v1GpiFailA OBJECT-TYPE
			SYNTAX BitFail
			MAX-ACCESS read-only
			STATUS current
			DESCRIPTION
				"Indicates external fail"
		::= { hfs3000c01v1Entry 49 }

		-- 1.3.6.1.4.1.10106.3.101291.1.1.50
		hfs3000c01v1GpiFailATrapEnable OBJECT-TYPE
			SYNTAX AlarmEnable
			MAX-ACCESS read-write
			STATUS current
			DESCRIPTION
				"Indicates external fail Trap Enable"
		::= { hfs3000c01v1Entry 50 }

		-- 1.3.6.1.4.1.10106.3.101291.1.1.51
		hfs3000c01v1NoSigB OBJECT-TYPE
			SYNTAX BitFail
			MAX-ACCESS read-only
			STATUS current
			DESCRIPTION
				"Indicates SDI signal fail"
		::= { hfs3000c01v1Entry 51 }

		-- 1.3.6.1.4.1.10106.3.101291.1.1.52
		hfs3000c01v1NoSigBTrapEnable OBJECT-TYPE
			SYNTAX AlarmEnable
			MAX-ACCESS read-write
			STATUS current
			DESCRIPTION
				"Indicates SDI signal fail Trap Enable"
		::= { hfs3000c01v1Entry 52 }

		-- 1.3.6.1.4.1.10106.3.101291.1.1.53
		hfs3000c01v1UnlockB OBJECT-TYPE
			SYNTAX BitFail
			MAX-ACCESS read-only
			STATUS current
			DESCRIPTION
				"Indicates signal unlock"
		::= { hfs3000c01v1Entry 53 }

		-- 1.3.6.1.4.1.10106.3.101291.1.1.54
		hfs3000c01v1UnlockBTrapEnable OBJECT-TYPE
			SYNTAX AlarmEnable
			MAX-ACCESS read-write
			STATUS current
			DESCRIPTION
				"Indicates signal unlock Trap Enable"
		::= { hfs3000c01v1Entry 54 }

		-- 1.3.6.1.4.1.10106.3.101291.1.1.55
		hfs3000c01v1EdhCrcB OBJECT-TYPE
			SYNTAX BitFail
			MAX-ACCESS read-only
			STATUS current
			DESCRIPTION
				"Indicates presence of EDH/CRC errors"
		::= { hfs3000c01v1Entry 55 }

		-- 1.3.6.1.4.1.10106.3.101291.1.1.56
		hfs3000c01v1EdhCrcBTrapEnable OBJECT-TYPE
			SYNTAX AlarmEnable
			MAX-ACCESS read-write
			STATUS current
			DESCRIPTION
				"Indicates presence of EDH/CRC errors Trap Enable"
		::= { hfs3000c01v1Entry 56 }

		-- 1.3.6.1.4.1.10106.3.101291.1.1.57
		hfs3000c01v1GpiFailB OBJECT-TYPE
			SYNTAX BitFail
			MAX-ACCESS read-only
			STATUS current
			DESCRIPTION
				"Indicates external fail"
		::= { hfs3000c01v1Entry 57 }

		-- 1.3.6.1.4.1.10106.3.101291.1.1.58
		hfs3000c01v1GpiFailBTrapEnable OBJECT-TYPE
			SYNTAX AlarmEnable
			MAX-ACCESS read-write
			STATUS current
			DESCRIPTION
				"Indicates external fail Trap Enable"
		::= { hfs3000c01v1Entry 58 }

		-- 1.3.6.1.4.1.10106.3.101291.1.1.59
		hfs3000c01v1NoRef OBJECT-TYPE
			SYNTAX BitFail
			MAX-ACCESS read-only
			STATUS current
			DESCRIPTION
				"Indicates reference signal fail"
		::= { hfs3000c01v1Entry 59 }

		-- 1.3.6.1.4.1.10106.3.101291.1.1.60
		hfs3000c01v1NoRefTrapEnable OBJECT-TYPE
			SYNTAX AlarmEnable
			MAX-ACCESS read-write
			STATUS current
			DESCRIPTION
				"Indicates reference signal fail Trap Enable"
		::= { hfs3000c01v1Entry 60 }

		-- 1.3.6.1.4.1.10106.3.101291.1.1.61
		hfs3000c01v1RefAUnlock OBJECT-TYPE
			SYNTAX BitFail
			MAX-ACCESS read-only
			STATUS current
			DESCRIPTION
				"Indicates reference signal unlock fail"
		::= { hfs3000c01v1Entry 61 }

		-- 1.3.6.1.4.1.10106.3.101291.1.1.62
		hfs3000c01v1RefAUnlockTrapEnable OBJECT-TYPE
			SYNTAX AlarmEnable
			MAX-ACCESS read-write
			STATUS current
			DESCRIPTION
				"Indicates reference signal unlock fail Trap Enable"
		::= { hfs3000c01v1Entry 62 }

		-- 1.3.6.1.4.1.10106.3.101291.1.1.63
		hfs3000c01v1RefBUnlock OBJECT-TYPE
			SYNTAX BitFail
			MAX-ACCESS read-only
			STATUS current
			DESCRIPTION
				"Indicates reference signal unlock fail"
		::= { hfs3000c01v1Entry 63 }

		-- 1.3.6.1.4.1.10106.3.101291.1.1.64
		hfs3000c01v1RefBUnlockTrapEnable OBJECT-TYPE
			SYNTAX AlarmEnable
			MAX-ACCESS read-write
			STATUS current
			DESCRIPTION
				"Indicates reference signal unlock fail Trap Enable"
		::= { hfs3000c01v1Entry 64 }

		-- 1.3.6.1.4.1.10106.3.101291.1.1.65
		hfs3000c01v1InputFormat OBJECT-TYPE
			SYNTAX SdiHd3gFmt3
			MAX-ACCESS read-only
			STATUS current
			DESCRIPTION
				"Indicates the reference signal format"
		::= { hfs3000c01v1Entry 65 }

		-- 1.3.6.1.4.1.10106.3.101291.1.1.67
		hfs3000c01v1SdiFormatA OBJECT-TYPE
			SYNTAX SdiHd3gFmt3
			MAX-ACCESS read-only
			STATUS current
			DESCRIPTION
				"Indicates the SDI input format"
		::= { hfs3000c01v1Entry 67 }

		-- 1.3.6.1.4.1.10106.3.101291.1.1.69
		hfs3000c01v1SdiFormatB OBJECT-TYPE
			SYNTAX SdiHd3gFmt3
			MAX-ACCESS read-only
			STATUS current
			DESCRIPTION
				"Indicates the SDI input format"
		::= { hfs3000c01v1Entry 69 }

		-- 1.3.6.1.4.1.10106.3.101291.1.1.71
		hfs3000c01v1SigDelayA OBJECT-TYPE
			SYNTAX DelayX20Us
			MAX-ACCESS read-only
			STATUS current
			DESCRIPTION
				"Indicates the input to output delay"
		::= { hfs3000c01v1Entry 71 }

		-- 1.3.6.1.4.1.10106.3.101291.1.1.73
		hfs3000c01v1SigDelayB OBJECT-TYPE
			SYNTAX DelayX20Us
			MAX-ACCESS read-only
			STATUS current
			DESCRIPTION
				"Indicates the input to output delay"
		::= { hfs3000c01v1Entry 73 }

		-- 1.3.6.1.4.1.10106.3.101291.1.1.75
		hfs3000c01v1SerialNo OBJECT-TYPE
			SYNTAX SerialNo
			MAX-ACCESS read-only
			STATUS current
			DESCRIPTION
				"Serial number"
		::= { hfs3000c01v1Entry 75 }

		-- 1.3.6.1.4.1.10106.3.357502
		hfs3000c01v2 OBJECT IDENTIFIER ::= { albalaProducts 357502 }

		-- 1.3.6.1.4.1.10106.3.357502.1
		hfs3000c01v2Table  OBJECT-TYPE
			SYNTAX SEQUENCE OF Hfs3000c01v2Entry
			MAX-ACCESS not-accessible
			STATUS current
			DESCRIPTION
				"Module  HFS3000C01V2 Table"
			::= { hfs3000c01v2 1 }

		-- 1.3.6.1.4.1.10106.3.357502.1.1
		hfs3000c01v2Entry  OBJECT-TYPE
			SYNTAX Hfs3000c01v2Entry
			MAX-ACCESS not-accessible
			STATUS current
			DESCRIPTION
				"Module HFS3000C01V2 Entry"
			INDEX { hfs3000c01v2Index }
			::= { hfs3000c01v2Table 1 }

			Hfs3000c01v2Entry ::=
			SEQUENCE {
				hfs3000c01v2Index
				ModuleIndex,
				hfs3000c01v2SynchroModeA
				Bit0Fra1Lin,
				hfs3000c01v2FailModeA
				Bit0Fre1Blk,
				hfs3000c01v2VbiModeA
				Bit0Pas1Bnk,
				hfs3000c01v2DelayModeA
				Bit0Syn1De2,
				hfs3000c01v2SynchroModeB
				Bit0Fra1Lin,
				hfs3000c01v2FailModeB
				Bit0Fre1Blk,
				hfs3000c01v2VbiModeB
				Bit0Pas1Bnk,
				hfs3000c01v2DelayModeB
				Bit0Syn1De2,
				hfs3000c01v2HDelayA
				DelayPixel5,
				hfs3000c01v2FrameDelayA
				DelayFram4,
				hfs3000c01v2VDelayA
				DelayLines2,
				hfs3000c01v2LumaGainA
				GainLin1,
				hfs3000c01v2ChromaGainA
				GainLin1,
				hfs3000c01v2BlackOffsetA
				BlackOffset1,
				hfs3000c01v2HDelayB
				DelayPixel5,
				hfs3000c01v2FrameDelayB
				DelayFram4,
				hfs3000c01v2VDelayB
				DelayLines2,
				hfs3000c01v2LumaGainB
				GainLin1,
				hfs3000c01v2ChromaGainB
				GainLin1,
				hfs3000c01v2BlackOffsetB
				BlackOffset1,
				hfs3000c01v2ClnGr1A
				Bit0No1Yes,
				hfs3000c01v2ClnGr2A
				Bit0No1Yes,
				hfs3000c01v2ClnGr3A
				Bit0No1Yes,
				hfs3000c01v2ClnGr4A
				Bit0No1Yes,
				hfs3000c01v2BitsA
				Bit020124,
				hfs3000c01v2Grp1P0A
				AudioMxInput5,
				hfs3000c01v2Grp1P1A
				AudioMxInput5,
				hfs3000c01v2Grp2P0A
				AudioMxInput5,
				hfs3000c01v2Grp2P1A
				AudioMxInput5,
				hfs3000c01v2Grp3P0A
				AudioMxInput5,
				hfs3000c01v2Grp3P1A
				AudioMxInput5,
				hfs3000c01v2Grp4P0A
				AudioMxInput5,
				hfs3000c01v2Grp4P1A
				AudioMxInput5,
				hfs3000c01v2ClnGr1B
				Bit0No1Yes,
				hfs3000c01v2ClnGr2B
				Bit0No1Yes,
				hfs3000c01v2ClnGr3B
				Bit0No1Yes,
				hfs3000c01v2ClnGr4B
				Bit0No1Yes,
				hfs3000c01v2BitsB
				Bit020124,
				hfs3000c01v2Grp1P0B
				AudioMxInput5,
				hfs3000c01v2Grp1P1B
				AudioMxInput5,
				hfs3000c01v2Grp2P0B
				AudioMxInput5,
				hfs3000c01v2Grp2P1B
				AudioMxInput5,
				hfs3000c01v2Grp3P0B
				AudioMxInput5,
				hfs3000c01v2Grp3P1B
				AudioMxInput5,
				hfs3000c01v2Grp4P0B
				AudioMxInput5,
				hfs3000c01v2Grp4P1B
				AudioMxInput5,
				hfs3000c01v2NoSigA
				BitFail,
				hfs3000c01v2NoSigATrapEnable
				AlarmEnable,
				hfs3000c01v2UnlockA
				BitFail,
				hfs3000c01v2UnlockATrapEnable
				AlarmEnable,
				hfs3000c01v2EdhCrcA
				BitFail,
				hfs3000c01v2EdhCrcATrapEnable
				AlarmEnable,
				hfs3000c01v2GpiFailA
				BitFail,
				hfs3000c01v2GpiFailATrapEnable
				AlarmEnable,
				hfs3000c01v2NoSigB
				BitFail,
				hfs3000c01v2NoSigBTrapEnable
				AlarmEnable,
				hfs3000c01v2UnlockB
				BitFail,
				hfs3000c01v2UnlockBTrapEnable
				AlarmEnable,
				hfs3000c01v2EdhCrcB
				BitFail,
				hfs3000c01v2EdhCrcBTrapEnable
				AlarmEnable,
				hfs3000c01v2GpiFailB
				BitFail,
				hfs3000c01v2GpiFailBTrapEnable
				AlarmEnable,
				hfs3000c01v2NoRef
				BitFail,
				hfs3000c01v2NoRefTrapEnable
				AlarmEnable,
				hfs3000c01v2RefAUnlock
				BitFail,
				hfs3000c01v2RefAUnlockTrapEnable
				AlarmEnable,
				hfs3000c01v2RefBUnlock
				BitFail,
				hfs3000c01v2RefBUnlockTrapEnable
				AlarmEnable,
				hfs3000c01v2InputFormat
				SdiHd3gFmt3,
				hfs3000c01v2SdiFormatA
				SdiHd3gFmt3,
				hfs3000c01v2SdiFormatB
				SdiHd3gFmt3,
				hfs3000c01v2SigDelayA
				DelayX20Us,
				hfs3000c01v2SigDelayB
				DelayX20Us,
				hfs3000c01v2Grp1APres
				Bit0No1Yes,
				hfs3000c01v2Grp2APres
				Bit0No1Yes,
				hfs3000c01v2Grp3APres
				Bit0No1Yes,
				hfs3000c01v2Grp4APres
				Bit0No1Yes,
				hfs3000c01v2Grp1BPres
				Bit0No1Yes,
				hfs3000c01v2Grp2BPres
				Bit0No1Yes,
				hfs3000c01v2Grp3BPres
				Bit0No1Yes,
				hfs3000c01v2Grp4BPres
				Bit0No1Yes,
				hfs3000c01v2Grp1P0AErr
				BitFail,
				hfs3000c01v2Grp1P1AErr
				BitFail,
				hfs3000c01v2Grp2P0AErr
				BitFail,
				hfs3000c01v2Grp2P1AErr
				BitFail,
				hfs3000c01v2Grp3P0AErr
				BitFail,
				hfs3000c01v2Grp3P1AErr
				BitFail,
				hfs3000c01v2Grp4P0AErr
				BitFail,
				hfs3000c01v2Grp4P1AErr
				BitFail,
				hfs3000c01v2Grp1P0BErr
				BitFail,
				hfs3000c01v2Grp1P1BErr
				BitFail,
				hfs3000c01v2Grp2P0BErr
				BitFail,
				hfs3000c01v2Grp2P1BErr
				BitFail,
				hfs3000c01v2Grp3P0BErr
				BitFail,
				hfs3000c01v2Grp3P1BErr
				BitFail,
				hfs3000c01v2Grp4P0BErr
				BitFail,
				hfs3000c01v2Grp4P1BErr
				BitFail,
				hfs3000c01v2SerialNo
				SerialNo
			 }

		-- 1.3.6.1.4.1.10106.3.101291.1.1.1
		hfs3000c01v2Index OBJECT-TYPE
			SYNTAX ModuleIndex
			MAX-ACCESS read-only
			STATUS current
			DESCRIPTION
				"Index of HFS3000C01V2 Table"
		::= { hfs3000c01v2Entry 1 }

		-- 1.3.6.1.4.1.10106.3.101291.1.1.3
		hfs3000c01v2SynchroModeA OBJECT-TYPE
			SYNTAX Bit0Fra1Lin
			MAX-ACCESS read-write
			STATUS current
			DESCRIPTION
				"Allows selecting the synchronizing mode"
		::= { hfs3000c01v2Entry 3 }

		-- 1.3.6.1.4.1.10106.3.101291.1.1.5
		hfs3000c01v2FailModeA OBJECT-TYPE
			SYNTAX Bit0Fre1Blk
			MAX-ACCESS read-write
			STATUS current
			DESCRIPTION
				"Allows selecting the output video signal if the input fails"
		::= { hfs3000c01v2Entry 5 }

		-- 1.3.6.1.4.1.10106.3.101291.1.1.7
		hfs3000c01v2VbiModeA OBJECT-TYPE
			SYNTAX Bit0Pas1Bnk
			MAX-ACCESS read-write
			STATUS current
			DESCRIPTION
				"Allows selecting if the VBI is blanked"
		::= { hfs3000c01v2Entry 7 }

		-- 1.3.6.1.4.1.10106.3.101291.1.1.9
		hfs3000c01v2DelayModeA OBJECT-TYPE
			SYNTAX Bit0Syn1De2
			MAX-ACCESS read-write
			STATUS current
			DESCRIPTION
				"Allows selecting the operating mode"
		::= { hfs3000c01v2Entry 9 }

		-- 1.3.6.1.4.1.10106.3.101291.1.1.11
		hfs3000c01v2SynchroModeB OBJECT-TYPE
			SYNTAX Bit0Fra1Lin
			MAX-ACCESS read-write
			STATUS current
			DESCRIPTION
				"Allows selecting the synchronizing mode"
		::= { hfs3000c01v2Entry 11 }

		-- 1.3.6.1.4.1.10106.3.101291.1.1.13
		hfs3000c01v2FailModeB OBJECT-TYPE
			SYNTAX Bit0Fre1Blk
			MAX-ACCESS read-write
			STATUS current
			DESCRIPTION
				"Allows selecting the output video signal if the input fails"
		::= { hfs3000c01v2Entry 13 }

		-- 1.3.6.1.4.1.10106.3.101291.1.1.15
		hfs3000c01v2VbiModeB OBJECT-TYPE
			SYNTAX Bit0Pas1Bnk
			MAX-ACCESS read-write
			STATUS current
			DESCRIPTION
				"Allows selecting if the VBI is blanked"
		::= { hfs3000c01v2Entry 15 }

		-- 1.3.6.1.4.1.10106.3.101291.1.1.17
		hfs3000c01v2DelayModeB OBJECT-TYPE
			SYNTAX Bit0Syn1De2
			MAX-ACCESS read-write
			STATUS current
			DESCRIPTION
				"Allows selecting the operating mode"
		::= { hfs3000c01v2Entry 17 }

		-- 1.3.6.1.4.1.10106.3.101291.1.1.19
		hfs3000c01v2HDelayA OBJECT-TYPE
			SYNTAX DelayPixel5
			MAX-ACCESS read-write
			STATUS current
			DESCRIPTION
				"Allows adjusting the video horizontal delay"
		::= { hfs3000c01v2Entry 19 }

		-- 1.3.6.1.4.1.10106.3.101291.1.1.21
		hfs3000c01v2FrameDelayA OBJECT-TYPE
			SYNTAX DelayFram4
			MAX-ACCESS read-write
			STATUS current
			DESCRIPTION
				"Allows adjusting the frame delay"
		::= { hfs3000c01v2Entry 21 }

		-- 1.3.6.1.4.1.10106.3.101291.1.1.23
		hfs3000c01v2VDelayA OBJECT-TYPE
			SYNTAX DelayLines2
			MAX-ACCESS read-write
			STATUS current
			DESCRIPTION
				"Allows adjusting the video vertical delay"
		::= { hfs3000c01v2Entry 23 }

		-- 1.3.6.1.4.1.10106.3.101291.1.1.25
		hfs3000c01v2LumaGainA OBJECT-TYPE
			SYNTAX GainLin1
			MAX-ACCESS read-write
			STATUS current
			DESCRIPTION
				"Allows adjusting the luma gain"
		::= { hfs3000c01v2Entry 25 }

		-- 1.3.6.1.4.1.10106.3.101291.1.1.27
		hfs3000c01v2ChromaGainA OBJECT-TYPE
			SYNTAX GainLin1
			MAX-ACCESS read-write
			STATUS current
			DESCRIPTION
				"Allows adjusting the chorma gain"
		::= { hfs3000c01v2Entry 27 }

		-- 1.3.6.1.4.1.10106.3.101291.1.1.29
		hfs3000c01v2BlackOffsetA OBJECT-TYPE
			SYNTAX BlackOffset1
			MAX-ACCESS read-write
			STATUS current
			DESCRIPTION
				"Allows adjusting the black offset"
		::= { hfs3000c01v2Entry 29 }

		-- 1.3.6.1.4.1.10106.3.101291.1.1.31
		hfs3000c01v2HDelayB OBJECT-TYPE
			SYNTAX DelayPixel5
			MAX-ACCESS read-write
			STATUS current
			DESCRIPTION
				"Allows adjusting the video horizontal delay"
		::= { hfs3000c01v2Entry 31 }

		-- 1.3.6.1.4.1.10106.3.101291.1.1.33
		hfs3000c01v2FrameDelayB OBJECT-TYPE
			SYNTAX DelayFram4
			MAX-ACCESS read-write
			STATUS current
			DESCRIPTION
				"Allows adjusting the frame delay"
		::= { hfs3000c01v2Entry 33 }

		-- 1.3.6.1.4.1.10106.3.101291.1.1.35
		hfs3000c01v2VDelayB OBJECT-TYPE
			SYNTAX DelayLines2
			MAX-ACCESS read-write
			STATUS current
			DESCRIPTION
				"Allows adjusting the video vertical delay"
		::= { hfs3000c01v2Entry 35 }

		-- 1.3.6.1.4.1.10106.3.101291.1.1.37
		hfs3000c01v2LumaGainB OBJECT-TYPE
			SYNTAX GainLin1
			MAX-ACCESS read-write
			STATUS current
			DESCRIPTION
				"Allows adjusting the luma gain"
		::= { hfs3000c01v2Entry 37 }

		-- 1.3.6.1.4.1.10106.3.101291.1.1.39
		hfs3000c01v2ChromaGainB OBJECT-TYPE
			SYNTAX GainLin1
			MAX-ACCESS read-write
			STATUS current
			DESCRIPTION
				"Allows adjusting the chorma gain"
		::= { hfs3000c01v2Entry 39 }

		-- 1.3.6.1.4.1.10106.3.101291.1.1.41
		hfs3000c01v2BlackOffsetB OBJECT-TYPE
			SYNTAX BlackOffset1
			MAX-ACCESS read-write
			STATUS current
			DESCRIPTION
				"Allows adjusting the black offset"
		::= { hfs3000c01v2Entry 41 }

		-- 1.3.6.1.4.1.10106.3.101291.1.1.43
		hfs3000c01v2ClnGr1A OBJECT-TYPE
			SYNTAX Bit0No1Yes
			MAX-ACCESS read-write
			STATUS current
			DESCRIPTION
				"Allows selecting if all the group 1 audio packets are deleted after deembedding"
		::= { hfs3000c01v2Entry 43 }

		-- 1.3.6.1.4.1.10106.3.101291.1.1.45
		hfs3000c01v2ClnGr2A OBJECT-TYPE
			SYNTAX Bit0No1Yes
			MAX-ACCESS read-write
			STATUS current
			DESCRIPTION
				"Allows selecting if all the group 2 audio packets are deleted after deembedding"
		::= { hfs3000c01v2Entry 45 }

		-- 1.3.6.1.4.1.10106.3.101291.1.1.47
		hfs3000c01v2ClnGr3A OBJECT-TYPE
			SYNTAX Bit0No1Yes
			MAX-ACCESS read-write
			STATUS current
			DESCRIPTION
				"Allows selecting if all the group 3 audio packets are deleted after deembedding"
		::= { hfs3000c01v2Entry 47 }

		-- 1.3.6.1.4.1.10106.3.101291.1.1.49
		hfs3000c01v2ClnGr4A OBJECT-TYPE
			SYNTAX Bit0No1Yes
			MAX-ACCESS read-write
			STATUS current
			DESCRIPTION
				"Allows selecting if all the group 4 audio packets are deleted after deembedding"
		::= { hfs3000c01v2Entry 49 }

		-- 1.3.6.1.4.1.10106.3.101291.1.1.51
		hfs3000c01v2BitsA OBJECT-TYPE
			SYNTAX Bit020124
			MAX-ACCESS read-write
			STATUS current
			DESCRIPTION
				"Allows selecting the number of bits"
		::= { hfs3000c01v2Entry 51 }

		-- 1.3.6.1.4.1.10106.3.101291.1.1.53
		hfs3000c01v2Grp1P0A OBJECT-TYPE
			SYNTAX AudioMxInput5
			MAX-ACCESS read-write
			STATUS current
			DESCRIPTION
				"Allows selecting the audio embedded in group 1 pair 0"
		::= { hfs3000c01v2Entry 53 }

		-- 1.3.6.1.4.1.10106.3.101291.1.1.55
		hfs3000c01v2Grp1P1A OBJECT-TYPE
			SYNTAX AudioMxInput5
			MAX-ACCESS read-write
			STATUS current
			DESCRIPTION
				"Allows selecting the audio embedded in group 1 pair 1"
		::= { hfs3000c01v2Entry 55 }

		-- 1.3.6.1.4.1.10106.3.101291.1.1.57
		hfs3000c01v2Grp2P0A OBJECT-TYPE
			SYNTAX AudioMxInput5
			MAX-ACCESS read-write
			STATUS current
			DESCRIPTION
				"Allows selecting the audio embedded in group 2 pair 0"
		::= { hfs3000c01v2Entry 57 }

		-- 1.3.6.1.4.1.10106.3.101291.1.1.59
		hfs3000c01v2Grp2P1A OBJECT-TYPE
			SYNTAX AudioMxInput5
			MAX-ACCESS read-write
			STATUS current
			DESCRIPTION
				"Allows selecting the audio embedded in group 2 pair 1"
		::= { hfs3000c01v2Entry 59 }

		-- 1.3.6.1.4.1.10106.3.101291.1.1.61
		hfs3000c01v2Grp3P0A OBJECT-TYPE
			SYNTAX AudioMxInput5
			MAX-ACCESS read-write
			STATUS current
			DESCRIPTION
				"Allows selecting the audio embedded in group 3 pair 0"
		::= { hfs3000c01v2Entry 61 }

		-- 1.3.6.1.4.1.10106.3.101291.1.1.63
		hfs3000c01v2Grp3P1A OBJECT-TYPE
			SYNTAX AudioMxInput5
			MAX-ACCESS read-write
			STATUS current
			DESCRIPTION
				"Allows selecting the audio embedded in group 3 pair 1"
		::= { hfs3000c01v2Entry 63 }

		-- 1.3.6.1.4.1.10106.3.101291.1.1.65
		hfs3000c01v2Grp4P0A OBJECT-TYPE
			SYNTAX AudioMxInput5
			MAX-ACCESS read-write
			STATUS current
			DESCRIPTION
				"Allows selecting the audio embedded in group 4 pair 0"
		::= { hfs3000c01v2Entry 65 }

		-- 1.3.6.1.4.1.10106.3.101291.1.1.67
		hfs3000c01v2Grp4P1A OBJECT-TYPE
			SYNTAX AudioMxInput5
			MAX-ACCESS read-write
			STATUS current
			DESCRIPTION
				"Allows selecting the audio embedded in group 4 pair 1"
		::= { hfs3000c01v2Entry 67 }

		-- 1.3.6.1.4.1.10106.3.101291.1.1.69
		hfs3000c01v2ClnGr1B OBJECT-TYPE
			SYNTAX Bit0No1Yes
			MAX-ACCESS read-write
			STATUS current
			DESCRIPTION
				"Allows selecting if all the group 1 audio packets are deleted after deembedding"
		::= { hfs3000c01v2Entry 69 }

		-- 1.3.6.1.4.1.10106.3.101291.1.1.71
		hfs3000c01v2ClnGr2B OBJECT-TYPE
			SYNTAX Bit0No1Yes
			MAX-ACCESS read-write
			STATUS current
			DESCRIPTION
				"Allows selecting if all the group 2 audio packets are deleted after deembedding"
		::= { hfs3000c01v2Entry 71 }

		-- 1.3.6.1.4.1.10106.3.101291.1.1.73
		hfs3000c01v2ClnGr3B OBJECT-TYPE
			SYNTAX Bit0No1Yes
			MAX-ACCESS read-write
			STATUS current
			DESCRIPTION
				"Allows selecting if all the group 3 audio packets are deleted after deembedding"
		::= { hfs3000c01v2Entry 73 }

		-- 1.3.6.1.4.1.10106.3.101291.1.1.75
		hfs3000c01v2ClnGr4B OBJECT-TYPE
			SYNTAX Bit0No1Yes
			MAX-ACCESS read-write
			STATUS current
			DESCRIPTION
				"Allows selecting if all the group 4 audio packets are deleted after deembedding"
		::= { hfs3000c01v2Entry 75 }

		-- 1.3.6.1.4.1.10106.3.101291.1.1.77
		hfs3000c01v2BitsB OBJECT-TYPE
			SYNTAX Bit020124
			MAX-ACCESS read-write
			STATUS current
			DESCRIPTION
				"Allows selecting the number of bits"
		::= { hfs3000c01v2Entry 77 }

		-- 1.3.6.1.4.1.10106.3.101291.1.1.79
		hfs3000c01v2Grp1P0B OBJECT-TYPE
			SYNTAX AudioMxInput5
			MAX-ACCESS read-write
			STATUS current
			DESCRIPTION
				"Allows selecting the audio embedded in group 1 pair 0"
		::= { hfs3000c01v2Entry 79 }

		-- 1.3.6.1.4.1.10106.3.101291.1.1.81
		hfs3000c01v2Grp1P1B OBJECT-TYPE
			SYNTAX AudioMxInput5
			MAX-ACCESS read-write
			STATUS current
			DESCRIPTION
				"Allows selecting the audio embedded in group 1 pair 1"
		::= { hfs3000c01v2Entry 81 }

		-- 1.3.6.1.4.1.10106.3.101291.1.1.83
		hfs3000c01v2Grp2P0B OBJECT-TYPE
			SYNTAX AudioMxInput5
			MAX-ACCESS read-write
			STATUS current
			DESCRIPTION
				"Allows selecting the audio embedded in group 2 pair 0"
		::= { hfs3000c01v2Entry 83 }

		-- 1.3.6.1.4.1.10106.3.101291.1.1.85
		hfs3000c01v2Grp2P1B OBJECT-TYPE
			SYNTAX AudioMxInput5
			MAX-ACCESS read-write
			STATUS current
			DESCRIPTION
				"Allows selecting the audio embedded in group 2 pair 1"
		::= { hfs3000c01v2Entry 85 }

		-- 1.3.6.1.4.1.10106.3.101291.1.1.87
		hfs3000c01v2Grp3P0B OBJECT-TYPE
			SYNTAX AudioMxInput5
			MAX-ACCESS read-write
			STATUS current
			DESCRIPTION
				"Allows selecting the audio embedded in group 3 pair 0"
		::= { hfs3000c01v2Entry 87 }

		-- 1.3.6.1.4.1.10106.3.101291.1.1.89
		hfs3000c01v2Grp3P1B OBJECT-TYPE
			SYNTAX AudioMxInput5
			MAX-ACCESS read-write
			STATUS current
			DESCRIPTION
				"Allows selecting the audio embedded in group 3 pair 1"
		::= { hfs3000c01v2Entry 89 }

		-- 1.3.6.1.4.1.10106.3.101291.1.1.91
		hfs3000c01v2Grp4P0B OBJECT-TYPE
			SYNTAX AudioMxInput5
			MAX-ACCESS read-write
			STATUS current
			DESCRIPTION
				"Allows selecting the audio embedded in group 4 pair 0"
		::= { hfs3000c01v2Entry 91 }

		-- 1.3.6.1.4.1.10106.3.101291.1.1.93
		hfs3000c01v2Grp4P1B OBJECT-TYPE
			SYNTAX AudioMxInput5
			MAX-ACCESS read-write
			STATUS current
			DESCRIPTION
				"Allows selecting the audio embedded in group 4 pair 1"
		::= { hfs3000c01v2Entry 93 }

		-- 1.3.6.1.4.1.10106.3.101291.1.1.95
		hfs3000c01v2NoSigA OBJECT-TYPE
			SYNTAX BitFail
			MAX-ACCESS read-only
			STATUS current
			DESCRIPTION
				"Indicates SDI signal fail"
		::= { hfs3000c01v2Entry 95 }

		-- 1.3.6.1.4.1.10106.3.101291.1.1.96
		hfs3000c01v2NoSigATrapEnable OBJECT-TYPE
			SYNTAX AlarmEnable
			MAX-ACCESS read-write
			STATUS current
			DESCRIPTION
				"Indicates SDI signal fail Trap Enable"
		::= { hfs3000c01v2Entry 96 }

		-- 1.3.6.1.4.1.10106.3.101291.1.1.97
		hfs3000c01v2UnlockA OBJECT-TYPE
			SYNTAX BitFail
			MAX-ACCESS read-only
			STATUS current
			DESCRIPTION
				"Indicates signal unlock"
		::= { hfs3000c01v2Entry 97 }

		-- 1.3.6.1.4.1.10106.3.101291.1.1.98
		hfs3000c01v2UnlockATrapEnable OBJECT-TYPE
			SYNTAX AlarmEnable
			MAX-ACCESS read-write
			STATUS current
			DESCRIPTION
				"Indicates signal unlock Trap Enable"
		::= { hfs3000c01v2Entry 98 }

		-- 1.3.6.1.4.1.10106.3.101291.1.1.99
		hfs3000c01v2EdhCrcA OBJECT-TYPE
			SYNTAX BitFail
			MAX-ACCESS read-only
			STATUS current
			DESCRIPTION
				"Indicates presence of EDH/CRC errors"
		::= { hfs3000c01v2Entry 99 }

		-- 1.3.6.1.4.1.10106.3.101291.1.1.100
		hfs3000c01v2EdhCrcATrapEnable OBJECT-TYPE
			SYNTAX AlarmEnable
			MAX-ACCESS read-write
			STATUS current
			DESCRIPTION
				"Indicates presence of EDH/CRC errors Trap Enable"
		::= { hfs3000c01v2Entry 100 }

		-- 1.3.6.1.4.1.10106.3.101291.1.1.101
		hfs3000c01v2GpiFailA OBJECT-TYPE
			SYNTAX BitFail
			MAX-ACCESS read-only
			STATUS current
			DESCRIPTION
				"Indicates external fail"
		::= { hfs3000c01v2Entry 101 }

		-- 1.3.6.1.4.1.10106.3.101291.1.1.102
		hfs3000c01v2GpiFailATrapEnable OBJECT-TYPE
			SYNTAX AlarmEnable
			MAX-ACCESS read-write
			STATUS current
			DESCRIPTION
				"Indicates external fail Trap Enable"
		::= { hfs3000c01v2Entry 102 }

		-- 1.3.6.1.4.1.10106.3.101291.1.1.103
		hfs3000c01v2NoSigB OBJECT-TYPE
			SYNTAX BitFail
			MAX-ACCESS read-only
			STATUS current
			DESCRIPTION
				"Indicates SDI signal fail"
		::= { hfs3000c01v2Entry 103 }

		-- 1.3.6.1.4.1.10106.3.101291.1.1.104
		hfs3000c01v2NoSigBTrapEnable OBJECT-TYPE
			SYNTAX AlarmEnable
			MAX-ACCESS read-write
			STATUS current
			DESCRIPTION
				"Indicates SDI signal fail Trap Enable"
		::= { hfs3000c01v2Entry 104 }

		-- 1.3.6.1.4.1.10106.3.101291.1.1.105
		hfs3000c01v2UnlockB OBJECT-TYPE
			SYNTAX BitFail
			MAX-ACCESS read-only
			STATUS current
			DESCRIPTION
				"Indicates signal unlock"
		::= { hfs3000c01v2Entry 105 }

		-- 1.3.6.1.4.1.10106.3.101291.1.1.106
		hfs3000c01v2UnlockBTrapEnable OBJECT-TYPE
			SYNTAX AlarmEnable
			MAX-ACCESS read-write
			STATUS current
			DESCRIPTION
				"Indicates signal unlock Trap Enable"
		::= { hfs3000c01v2Entry 106 }

		-- 1.3.6.1.4.1.10106.3.101291.1.1.107
		hfs3000c01v2EdhCrcB OBJECT-TYPE
			SYNTAX BitFail
			MAX-ACCESS read-only
			STATUS current
			DESCRIPTION
				"Indicates presence of EDH/CRC errors"
		::= { hfs3000c01v2Entry 107 }

		-- 1.3.6.1.4.1.10106.3.101291.1.1.108
		hfs3000c01v2EdhCrcBTrapEnable OBJECT-TYPE
			SYNTAX AlarmEnable
			MAX-ACCESS read-write
			STATUS current
			DESCRIPTION
				"Indicates presence of EDH/CRC errors Trap Enable"
		::= { hfs3000c01v2Entry 108 }

		-- 1.3.6.1.4.1.10106.3.101291.1.1.109
		hfs3000c01v2GpiFailB OBJECT-TYPE
			SYNTAX BitFail
			MAX-ACCESS read-only
			STATUS current
			DESCRIPTION
				"Indicates external fail"
		::= { hfs3000c01v2Entry 109 }

		-- 1.3.6.1.4.1.10106.3.101291.1.1.110
		hfs3000c01v2GpiFailBTrapEnable OBJECT-TYPE
			SYNTAX AlarmEnable
			MAX-ACCESS read-write
			STATUS current
			DESCRIPTION
				"Indicates external fail Trap Enable"
		::= { hfs3000c01v2Entry 110 }

		-- 1.3.6.1.4.1.10106.3.101291.1.1.111
		hfs3000c01v2NoRef OBJECT-TYPE
			SYNTAX BitFail
			MAX-ACCESS read-only
			STATUS current
			DESCRIPTION
				"Indicates reference signal fail"
		::= { hfs3000c01v2Entry 111 }

		-- 1.3.6.1.4.1.10106.3.101291.1.1.112
		hfs3000c01v2NoRefTrapEnable OBJECT-TYPE
			SYNTAX AlarmEnable
			MAX-ACCESS read-write
			STATUS current
			DESCRIPTION
				"Indicates reference signal fail Trap Enable"
		::= { hfs3000c01v2Entry 112 }

		-- 1.3.6.1.4.1.10106.3.101291.1.1.113
		hfs3000c01v2RefAUnlock OBJECT-TYPE
			SYNTAX BitFail
			MAX-ACCESS read-only
			STATUS current
			DESCRIPTION
				"Indicates reference signal unlock fail"
		::= { hfs3000c01v2Entry 113 }

		-- 1.3.6.1.4.1.10106.3.101291.1.1.114
		hfs3000c01v2RefAUnlockTrapEnable OBJECT-TYPE
			SYNTAX AlarmEnable
			MAX-ACCESS read-write
			STATUS current
			DESCRIPTION
				"Indicates reference signal unlock fail Trap Enable"
		::= { hfs3000c01v2Entry 114 }

		-- 1.3.6.1.4.1.10106.3.101291.1.1.115
		hfs3000c01v2RefBUnlock OBJECT-TYPE
			SYNTAX BitFail
			MAX-ACCESS read-only
			STATUS current
			DESCRIPTION
				"Indicates reference signal unlock fail"
		::= { hfs3000c01v2Entry 115 }

		-- 1.3.6.1.4.1.10106.3.101291.1.1.116
		hfs3000c01v2RefBUnlockTrapEnable OBJECT-TYPE
			SYNTAX AlarmEnable
			MAX-ACCESS read-write
			STATUS current
			DESCRIPTION
				"Indicates reference signal unlock fail Trap Enable"
		::= { hfs3000c01v2Entry 116 }

		-- 1.3.6.1.4.1.10106.3.101291.1.1.117
		hfs3000c01v2InputFormat OBJECT-TYPE
			SYNTAX SdiHd3gFmt3
			MAX-ACCESS read-only
			STATUS current
			DESCRIPTION
				"Indicates the reference signal format"
		::= { hfs3000c01v2Entry 117 }

		-- 1.3.6.1.4.1.10106.3.101291.1.1.119
		hfs3000c01v2SdiFormatA OBJECT-TYPE
			SYNTAX SdiHd3gFmt3
			MAX-ACCESS read-only
			STATUS current
			DESCRIPTION
				"Indicates the SDI input format"
		::= { hfs3000c01v2Entry 119 }

		-- 1.3.6.1.4.1.10106.3.101291.1.1.121
		hfs3000c01v2SdiFormatB OBJECT-TYPE
			SYNTAX SdiHd3gFmt3
			MAX-ACCESS read-only
			STATUS current
			DESCRIPTION
				"Indicates the SDI input format"
		::= { hfs3000c01v2Entry 121 }

		-- 1.3.6.1.4.1.10106.3.101291.1.1.123
		hfs3000c01v2SigDelayA OBJECT-TYPE
			SYNTAX DelayX20Us
			MAX-ACCESS read-only
			STATUS current
			DESCRIPTION
				"Indicates the input to output delay"
		::= { hfs3000c01v2Entry 123 }

		-- 1.3.6.1.4.1.10106.3.101291.1.1.125
		hfs3000c01v2SigDelayB OBJECT-TYPE
			SYNTAX DelayX20Us
			MAX-ACCESS read-only
			STATUS current
			DESCRIPTION
				"Indicates the input to output delay"
		::= { hfs3000c01v2Entry 125 }

		-- 1.3.6.1.4.1.10106.3.101291.1.1.127
		hfs3000c01v2Grp1APres OBJECT-TYPE
			SYNTAX Bit0No1Yes
			MAX-ACCESS read-only
			STATUS current
			DESCRIPTION
				"Group 1 presence"
		::= { hfs3000c01v2Entry 127 }

		-- 1.3.6.1.4.1.10106.3.101291.1.1.129
		hfs3000c01v2Grp2APres OBJECT-TYPE
			SYNTAX Bit0No1Yes
			MAX-ACCESS read-only
			STATUS current
			DESCRIPTION
				"Group 2 presence"
		::= { hfs3000c01v2Entry 129 }

		-- 1.3.6.1.4.1.10106.3.101291.1.1.131
		hfs3000c01v2Grp3APres OBJECT-TYPE
			SYNTAX Bit0No1Yes
			MAX-ACCESS read-only
			STATUS current
			DESCRIPTION
				"Group 3 presence"
		::= { hfs3000c01v2Entry 131 }

		-- 1.3.6.1.4.1.10106.3.101291.1.1.133
		hfs3000c01v2Grp4APres OBJECT-TYPE
			SYNTAX Bit0No1Yes
			MAX-ACCESS read-only
			STATUS current
			DESCRIPTION
				"Group 4 presence"
		::= { hfs3000c01v2Entry 133 }

		-- 1.3.6.1.4.1.10106.3.101291.1.1.135
		hfs3000c01v2Grp1BPres OBJECT-TYPE
			SYNTAX Bit0No1Yes
			MAX-ACCESS read-only
			STATUS current
			DESCRIPTION
				"Group 1 presence"
		::= { hfs3000c01v2Entry 135 }

		-- 1.3.6.1.4.1.10106.3.101291.1.1.137
		hfs3000c01v2Grp2BPres OBJECT-TYPE
			SYNTAX Bit0No1Yes
			MAX-ACCESS read-only
			STATUS current
			DESCRIPTION
				"Group 2 presence"
		::= { hfs3000c01v2Entry 137 }

		-- 1.3.6.1.4.1.10106.3.101291.1.1.139
		hfs3000c01v2Grp3BPres OBJECT-TYPE
			SYNTAX Bit0No1Yes
			MAX-ACCESS read-only
			STATUS current
			DESCRIPTION
				"Group 3 presence"
		::= { hfs3000c01v2Entry 139 }

		-- 1.3.6.1.4.1.10106.3.101291.1.1.141
		hfs3000c01v2Grp4BPres OBJECT-TYPE
			SYNTAX Bit0No1Yes
			MAX-ACCESS read-only
			STATUS current
			DESCRIPTION
				"Group 4 presence"
		::= { hfs3000c01v2Entry 141 }

		-- 1.3.6.1.4.1.10106.3.101291.1.1.143
		hfs3000c01v2Grp1P0AErr OBJECT-TYPE
			SYNTAX BitFail
			MAX-ACCESS read-only
			STATUS current
			DESCRIPTION
				"SDI A group 1 pair 0 fail"
		::= { hfs3000c01v2Entry 143 }

		-- 1.3.6.1.4.1.10106.3.101291.1.1.145
		hfs3000c01v2Grp1P1AErr OBJECT-TYPE
			SYNTAX BitFail
			MAX-ACCESS read-only
			STATUS current
			DESCRIPTION
				"SDI A group 1 pair 1 fail"
		::= { hfs3000c01v2Entry 145 }

		-- 1.3.6.1.4.1.10106.3.101291.1.1.147
		hfs3000c01v2Grp2P0AErr OBJECT-TYPE
			SYNTAX BitFail
			MAX-ACCESS read-only
			STATUS current
			DESCRIPTION
				"SDI A group 2 pair 0 fail"
		::= { hfs3000c01v2Entry 147 }

		-- 1.3.6.1.4.1.10106.3.101291.1.1.149
		hfs3000c01v2Grp2P1AErr OBJECT-TYPE
			SYNTAX BitFail
			MAX-ACCESS read-only
			STATUS current
			DESCRIPTION
				"SDI A group 2 pair 1 fail"
		::= { hfs3000c01v2Entry 149 }

		-- 1.3.6.1.4.1.10106.3.101291.1.1.151
		hfs3000c01v2Grp3P0AErr OBJECT-TYPE
			SYNTAX BitFail
			MAX-ACCESS read-only
			STATUS current
			DESCRIPTION
				"SDI A group 3 pair 0 fail"
		::= { hfs3000c01v2Entry 151 }

		-- 1.3.6.1.4.1.10106.3.101291.1.1.153
		hfs3000c01v2Grp3P1AErr OBJECT-TYPE
			SYNTAX BitFail
			MAX-ACCESS read-only
			STATUS current
			DESCRIPTION
				"SDI A group 3 pair 1 fail"
		::= { hfs3000c01v2Entry 153 }

		-- 1.3.6.1.4.1.10106.3.101291.1.1.155
		hfs3000c01v2Grp4P0AErr OBJECT-TYPE
			SYNTAX BitFail
			MAX-ACCESS read-only
			STATUS current
			DESCRIPTION
				"SDI A group 4 pair 0 fail"
		::= { hfs3000c01v2Entry 155 }

		-- 1.3.6.1.4.1.10106.3.101291.1.1.157
		hfs3000c01v2Grp4P1AErr OBJECT-TYPE
			SYNTAX BitFail
			MAX-ACCESS read-only
			STATUS current
			DESCRIPTION
				"SDI A group 4 pair 1 fail"
		::= { hfs3000c01v2Entry 157 }

		-- 1.3.6.1.4.1.10106.3.101291.1.1.159
		hfs3000c01v2Grp1P0BErr OBJECT-TYPE
			SYNTAX BitFail
			MAX-ACCESS read-only
			STATUS current
			DESCRIPTION
				"SDI B group 1 pair 0 fail"
		::= { hfs3000c01v2Entry 159 }

		-- 1.3.6.1.4.1.10106.3.101291.1.1.161
		hfs3000c01v2Grp1P1BErr OBJECT-TYPE
			SYNTAX BitFail
			MAX-ACCESS read-only
			STATUS current
			DESCRIPTION
				"SDI B group 1 pair 1 fail"
		::= { hfs3000c01v2Entry 161 }

		-- 1.3.6.1.4.1.10106.3.101291.1.1.163
		hfs3000c01v2Grp2P0BErr OBJECT-TYPE
			SYNTAX BitFail
			MAX-ACCESS read-only
			STATUS current
			DESCRIPTION
				"SDI B group 2 pair 0 fail"
		::= { hfs3000c01v2Entry 163 }

		-- 1.3.6.1.4.1.10106.3.101291.1.1.165
		hfs3000c01v2Grp2P1BErr OBJECT-TYPE
			SYNTAX BitFail
			MAX-ACCESS read-only
			STATUS current
			DESCRIPTION
				"SDI B group 2 pair 1 fail"
		::= { hfs3000c01v2Entry 165 }

		-- 1.3.6.1.4.1.10106.3.101291.1.1.167
		hfs3000c01v2Grp3P0BErr OBJECT-TYPE
			SYNTAX BitFail
			MAX-ACCESS read-only
			STATUS current
			DESCRIPTION
				"SDI B group 3 pair 0 fail"
		::= { hfs3000c01v2Entry 167 }

		-- 1.3.6.1.4.1.10106.3.101291.1.1.169
		hfs3000c01v2Grp3P1BErr OBJECT-TYPE
			SYNTAX BitFail
			MAX-ACCESS read-only
			STATUS current
			DESCRIPTION
				"SDI B group 3 pair 1 fail"
		::= { hfs3000c01v2Entry 169 }

		-- 1.3.6.1.4.1.10106.3.101291.1.1.171
		hfs3000c01v2Grp4P0BErr OBJECT-TYPE
			SYNTAX BitFail
			MAX-ACCESS read-only
			STATUS current
			DESCRIPTION
				"SDI B group 4 pair 0 fail"
		::= { hfs3000c01v2Entry 171 }

		-- 1.3.6.1.4.1.10106.3.101291.1.1.173
		hfs3000c01v2Grp4P1BErr OBJECT-TYPE
			SYNTAX BitFail
			MAX-ACCESS read-only
			STATUS current
			DESCRIPTION
				"SDI B group 4 pair 1 fail"
		::= { hfs3000c01v2Entry 173 }

		-- 1.3.6.1.4.1.10106.3.101291.1.1.175
		hfs3000c01v2SerialNo OBJECT-TYPE
			SYNTAX SerialNo
			MAX-ACCESS read-only
			STATUS current
			DESCRIPTION
				"Serial number"
		::= { hfs3000c01v2Entry 175 }

		-- 1.3.6.1.4.1.10106.3.358101
		hde3000c01v1 OBJECT IDENTIFIER ::= { albalaProducts 358101 }

		-- 1.3.6.1.4.1.10106.3.358101.1
		hde3000c01v1Table  OBJECT-TYPE
			SYNTAX SEQUENCE OF Hde3000c01v1Entry
			MAX-ACCESS not-accessible
			STATUS current
			DESCRIPTION
				"Module  HDE3000C01V1 Table"
			::= { hde3000c01v1 1 }

		-- 1.3.6.1.4.1.10106.3.358101.1.1
		hde3000c01v1Entry  OBJECT-TYPE
			SYNTAX Hde3000c01v1Entry
			MAX-ACCESS not-accessible
			STATUS current
			DESCRIPTION
				"Module HDE3000C01V1 Entry"
			INDEX { hde3000c01v1Index }
			::= { hde3000c01v1Table 1 }

			Hde3000c01v1Entry ::=
			SEQUENCE {
				hde3000c01v1Index
				ModuleIndex,
				hde3000c01v1RestorPreset
				PresetRestore,
				hde3000c01v1ActivePreset
				PresetActive,
				hde3000c01v1LoadPreset
				PresetLoad,
				hde3000c01v1SavePreset
				PresetSave,
				hde3000c01v1ClnGr1A
				Bit0No1Yes,
				hde3000c01v1ClnGr2A
				Bit0No1Yes,
				hde3000c01v1ClnGr3A
				Bit0No1Yes,
				hde3000c01v1ClnGr4A
				Bit0No1Yes,
				hde3000c01v1ClnGr1B
				Bit0No1Yes,
				hde3000c01v1ClnGr2B
				Bit0No1Yes,
				hde3000c01v1ClnGr3B
				Bit0No1Yes,
				hde3000c01v1ClnGr4B
				Bit0No1Yes,
				hde3000c01v1Grp1P0A
				AudioMxInput1,
				hde3000c01v1Grp1P1A
				AudioMxInput1,
				hde3000c01v1Grp2P0A
				AudioMxInput1,
				hde3000c01v1Grp2P1A
				AudioMxInput1,
				hde3000c01v1Grp3P0A
				AudioMxInput1,
				hde3000c01v1Grp3P1A
				AudioMxInput1,
				hde3000c01v1Grp4P0A
				AudioMxInput1,
				hde3000c01v1Grp4P1A
				AudioMxInput1,
				hde3000c01v1Grp1P0B
				AudioMxInput1,
				hde3000c01v1Grp1P1B
				AudioMxInput1,
				hde3000c01v1Grp2P0B
				AudioMxInput1,
				hde3000c01v1Grp2P1B
				AudioMxInput1,
				hde3000c01v1Grp3P0B
				AudioMxInput1,
				hde3000c01v1Grp3P1B
				AudioMxInput1,
				hde3000c01v1Grp4P0B
				AudioMxInput1,
				hde3000c01v1Grp4P1B
				AudioMxInput1,
				hde3000c01v1Aes1A
				AudioMxInput2,
				hde3000c01v1Aes2A
				AudioMxInput2,
				hde3000c01v1Aes3A
				AudioMxInput2,
				hde3000c01v1Aes4A
				AudioMxInput2,
				hde3000c01v1Aes1B
				AudioMxInput2,
				hde3000c01v1Aes2B
				AudioMxInput2,
				hde3000c01v1Aes3B
				AudioMxInput2,
				hde3000c01v1Aes4B
				AudioMxInput2,
				hde3000c01v1OvldLevel
				LevelDbfs4,
				hde3000c01v1SilenceLevel
				LevelDbfs3,
				hde3000c01v1SilenceTime
				TimeS2,
				hde3000c01v1DelayMode
				Bit0Out1In,
				hde3000c01v1DelaySteps
				TimeX1Ms,
				hde3000c01v1Grp1P0AGain
				Gain24dbMute,
				hde3000c01v1Grp1P1AGain
				Gain24dbMute,
				hde3000c01v1Grp2P0AGain
				Gain24dbMute,
				hde3000c01v1Grp2P1AGain
				Gain24dbMute,
				hde3000c01v1Grp3P0AGain
				Gain24dbMute,
				hde3000c01v1Grp3P1AGain
				Gain24dbMute,
				hde3000c01v1Grp4P0AGain
				Gain24dbMute,
				hde3000c01v1Grp4P1AGain
				Gain24dbMute,
				hde3000c01v1Grp1P0BGain
				Gain24dbMute,
				hde3000c01v1Grp1P1BGain
				Gain24dbMute,
				hde3000c01v1Grp2P0BGain
				Gain24dbMute,
				hde3000c01v1Grp2P1BGain
				Gain24dbMute,
				hde3000c01v1Grp3P0BGain
				Gain24dbMute,
				hde3000c01v1Grp3P1BGain
				Gain24dbMute,
				hde3000c01v1Grp4P0BGain
				Gain24dbMute,
				hde3000c01v1Grp4P1BGain
				Gain24dbMute,
				hde3000c01v1Aes1AGain
				Gain24dbMute,
				hde3000c01v1Aes2AGain
				Gain24dbMute,
				hde3000c01v1Aes3AGain
				Gain24dbMute,
				hde3000c01v1Aes4AGain
				Gain24dbMute,
				hde3000c01v1Aes1BGain
				Gain24dbMute,
				hde3000c01v1Aes2BGain
				Gain24dbMute,
				hde3000c01v1Aes3BGain
				Gain24dbMute,
				hde3000c01v1Aes4BGain
				Gain24dbMute,
				hde3000c01v1Grp1P0ADelay
				Uint8,
				hde3000c01v1Grp1P1ADelay
				Uint8,
				hde3000c01v1Grp2P0ADelay
				Uint8,
				hde3000c01v1Grp2P1ADelay
				Uint8,
				hde3000c01v1Grp3P0ADelay
				Uint8,
				hde3000c01v1Grp3P1ADelay
				Uint8,
				hde3000c01v1Grp4P0ADelay
				Uint8,
				hde3000c01v1Grp4P1ADelay
				Uint8,
				hde3000c01v1Grp1P0BDelay
				Uint8,
				hde3000c01v1Grp1P1BDelay
				Uint8,
				hde3000c01v1Grp2P0BDelay
				Uint8,
				hde3000c01v1Grp2P1BDelay
				Uint8,
				hde3000c01v1Grp3P0BDelay
				Uint8,
				hde3000c01v1Grp3P1BDelay
				Uint8,
				hde3000c01v1Grp4P0BDelay
				Uint8,
				hde3000c01v1Grp4P1BDelay
				Uint8,
				hde3000c01v1Aes1ADelay
				Uint8,
				hde3000c01v1Aes2ADelay
				Uint8,
				hde3000c01v1Aes3ADelay
				Uint8,
				hde3000c01v1Aes4ADelay
				Uint8,
				hde3000c01v1Aes1BDelay
				Uint8,
				hde3000c01v1Aes2BDelay
				Uint8,
				hde3000c01v1Aes3BDelay
				Uint8,
				hde3000c01v1Aes4BDelay
				Uint8,
				hde3000c01v1NoSignalA
				BitFail,
				hde3000c01v1NoSignalATrapEnable
				AlarmEnable,
				hde3000c01v1UnlockA
				BitFail,
				hde3000c01v1UnlockATrapEnable
				AlarmEnable,
				hde3000c01v1EdhErrorA
				BitFail,
				hde3000c01v1EdhErrorATrapEnable
				AlarmEnable,
				hde3000c01v1AesFailA
				BitFail,
				hde3000c01v1AesFailATrapEnable
				AlarmEnable,
				hde3000c01v1DeemFailA
				BitFail,
				hde3000c01v1DeemFailATrapEnable
				AlarmEnable,
				hde3000c01v1AesOvlA
				BitFail,
				hde3000c01v1AesOvlATrapEnable
				AlarmEnable,
				hde3000c01v1DeemOvlA
				BitFail,
				hde3000c01v1DeemOvlATrapEnable
				AlarmEnable,
				hde3000c01v1FormatA
				SdiHd3gFmt3,
				hde3000c01v1NoSignalB
				BitFail,
				hde3000c01v1NoSignalBTrapEnable
				AlarmEnable,
				hde3000c01v1UnlockB
				BitFail,
				hde3000c01v1UnlockBTrapEnable
				AlarmEnable,
				hde3000c01v1EdhErrorB
				BitFail,
				hde3000c01v1EdhErrorBTrapEnable
				AlarmEnable,
				hde3000c01v1AesFailB
				BitFail,
				hde3000c01v1AesFailBTrapEnable
				AlarmEnable,
				hde3000c01v1DeemFailB
				BitFail,
				hde3000c01v1DeemFailBTrapEnable
				AlarmEnable,
				hde3000c01v1AesOvlB
				BitFail,
				hde3000c01v1AesOvlBTrapEnable
				AlarmEnable,
				hde3000c01v1DeemOvlB
				BitFail,
				hde3000c01v1DeemOvlBTrapEnable
				AlarmEnable,
				hde3000c01v1FormatB
				SdiHd3gFmt3,
				hde3000c01v1SerialNo
				SerialNo,
				hde3000c01v1CorteSelChB
				Bit0BlBit1Cut
			 }

		-- 1.3.6.1.4.1.10106.3.101291.1.1.1
		hde3000c01v1Index OBJECT-TYPE
			SYNTAX ModuleIndex
			MAX-ACCESS read-only
			STATUS current
			DESCRIPTION
				"Index of HDE3000C01V1 Table"
		::= { hde3000c01v1Entry 1 }

		-- 1.3.6.1.4.1.10106.3.101291.1.1.3
		hde3000c01v1RestorPreset OBJECT-TYPE
			SYNTAX PresetRestore
			MAX-ACCESS read-write
			STATUS current
			DESCRIPTION
				"Allows restoring a factory preset"
		::= { hde3000c01v1Entry 3 }

		-- 1.3.6.1.4.1.10106.3.101291.1.1.5
		hde3000c01v1ActivePreset OBJECT-TYPE
			SYNTAX PresetActive
			MAX-ACCESS read-only
			STATUS current
			DESCRIPTION
				"Shows the active preset"
		::= { hde3000c01v1Entry 5 }

		-- 1.3.6.1.4.1.10106.3.101291.1.1.7
		hde3000c01v1LoadPreset OBJECT-TYPE
			SYNTAX PresetLoad
			MAX-ACCESS read-write
			STATUS current
			DESCRIPTION
				"Allows loading a preset"
		::= { hde3000c01v1Entry 7 }

		-- 1.3.6.1.4.1.10106.3.101291.1.1.9
		hde3000c01v1SavePreset OBJECT-TYPE
			SYNTAX PresetSave
			MAX-ACCESS read-write
			STATUS current
			DESCRIPTION
				"Allows saving a preset"
		::= { hde3000c01v1Entry 9 }

		-- 1.3.6.1.4.1.10106.3.101291.1.1.11
		hde3000c01v1ClnGr1A OBJECT-TYPE
			SYNTAX Bit0No1Yes
			MAX-ACCESS read-write
			STATUS current
			DESCRIPTION
				"Allows selecting if all the group 1 audio packets are deleted after deembedding"
		::= { hde3000c01v1Entry 11 }

		-- 1.3.6.1.4.1.10106.3.101291.1.1.13
		hde3000c01v1ClnGr2A OBJECT-TYPE
			SYNTAX Bit0No1Yes
			MAX-ACCESS read-write
			STATUS current
			DESCRIPTION
				"Allows selecting if all the group 2 audio packets are deleted after deembedding"
		::= { hde3000c01v1Entry 13 }

		-- 1.3.6.1.4.1.10106.3.101291.1.1.15
		hde3000c01v1ClnGr3A OBJECT-TYPE
			SYNTAX Bit0No1Yes
			MAX-ACCESS read-write
			STATUS current
			DESCRIPTION
				"Allows selecting if all the group 3 audio packets are deleted after deembedding"
		::= { hde3000c01v1Entry 15 }

		-- 1.3.6.1.4.1.10106.3.101291.1.1.17
		hde3000c01v1ClnGr4A OBJECT-TYPE
			SYNTAX Bit0No1Yes
			MAX-ACCESS read-write
			STATUS current
			DESCRIPTION
				"Allows selecting if all the group 4 audio packets are deleted after deembedding"
		::= { hde3000c01v1Entry 17 }

		-- 1.3.6.1.4.1.10106.3.101291.1.1.19
		hde3000c01v1ClnGr1B OBJECT-TYPE
			SYNTAX Bit0No1Yes
			MAX-ACCESS read-write
			STATUS current
			DESCRIPTION
				"Allows selecting if all the group 1 audio packets are deleted after deembedding"
		::= { hde3000c01v1Entry 19 }

		-- 1.3.6.1.4.1.10106.3.101291.1.1.21
		hde3000c01v1ClnGr2B OBJECT-TYPE
			SYNTAX Bit0No1Yes
			MAX-ACCESS read-write
			STATUS current
			DESCRIPTION
				"Allows selecting if all the group 2 audio packets are deleted after deembedding"
		::= { hde3000c01v1Entry 21 }

		-- 1.3.6.1.4.1.10106.3.101291.1.1.23
		hde3000c01v1ClnGr3B OBJECT-TYPE
			SYNTAX Bit0No1Yes
			MAX-ACCESS read-write
			STATUS current
			DESCRIPTION
				"Allows selecting if all the group 3 audio packets are deleted after deembedding"
		::= { hde3000c01v1Entry 23 }

		-- 1.3.6.1.4.1.10106.3.101291.1.1.25
		hde3000c01v1ClnGr4B OBJECT-TYPE
			SYNTAX Bit0No1Yes
			MAX-ACCESS read-write
			STATUS current
			DESCRIPTION
				"Allows selecting if all the group 4 audio packets are deleted after deembedding"
		::= { hde3000c01v1Entry 25 }

		-- 1.3.6.1.4.1.10106.3.101291.1.1.27
		hde3000c01v1Grp1P0A OBJECT-TYPE
			SYNTAX AudioMxInput1
			MAX-ACCESS read-write
			STATUS current
			DESCRIPTION
				"Allows selecting the audio embedded in group 1 pair 0"
		::= { hde3000c01v1Entry 27 }

		-- 1.3.6.1.4.1.10106.3.101291.1.1.29
		hde3000c01v1Grp1P1A OBJECT-TYPE
			SYNTAX AudioMxInput1
			MAX-ACCESS read-write
			STATUS current
			DESCRIPTION
				"Allows selecting the audio embedded in group 1 pair 1"
		::= { hde3000c01v1Entry 29 }

		-- 1.3.6.1.4.1.10106.3.101291.1.1.31
		hde3000c01v1Grp2P0A OBJECT-TYPE
			SYNTAX AudioMxInput1
			MAX-ACCESS read-write
			STATUS current
			DESCRIPTION
				"Allows selecting the audio embedded in group 2 pair 0"
		::= { hde3000c01v1Entry 31 }

		-- 1.3.6.1.4.1.10106.3.101291.1.1.33
		hde3000c01v1Grp2P1A OBJECT-TYPE
			SYNTAX AudioMxInput1
			MAX-ACCESS read-write
			STATUS current
			DESCRIPTION
				"Allows selecting the audio embedded in group 2 pair 1"
		::= { hde3000c01v1Entry 33 }

		-- 1.3.6.1.4.1.10106.3.101291.1.1.35
		hde3000c01v1Grp3P0A OBJECT-TYPE
			SYNTAX AudioMxInput1
			MAX-ACCESS read-write
			STATUS current
			DESCRIPTION
				"Allows selecting the audio embedded in group 3 pair 0"
		::= { hde3000c01v1Entry 35 }

		-- 1.3.6.1.4.1.10106.3.101291.1.1.37
		hde3000c01v1Grp3P1A OBJECT-TYPE
			SYNTAX AudioMxInput1
			MAX-ACCESS read-write
			STATUS current
			DESCRIPTION
				"Allows selecting the audio embedded in group 3 pair 1"
		::= { hde3000c01v1Entry 37 }

		-- 1.3.6.1.4.1.10106.3.101291.1.1.39
		hde3000c01v1Grp4P0A OBJECT-TYPE
			SYNTAX AudioMxInput1
			MAX-ACCESS read-write
			STATUS current
			DESCRIPTION
				"Allows selecting the audio embedded in group 4 pair 0"
		::= { hde3000c01v1Entry 39 }

		-- 1.3.6.1.4.1.10106.3.101291.1.1.41
		hde3000c01v1Grp4P1A OBJECT-TYPE
			SYNTAX AudioMxInput1
			MAX-ACCESS read-write
			STATUS current
			DESCRIPTION
				"Allows selecting the audio embedded in group 4 pair 1"
		::= { hde3000c01v1Entry 41 }

		-- 1.3.6.1.4.1.10106.3.101291.1.1.43
		hde3000c01v1Grp1P0B OBJECT-TYPE
			SYNTAX AudioMxInput1
			MAX-ACCESS read-write
			STATUS current
			DESCRIPTION
				"Allows selecting the audio embedded in group 1 pair 0"
		::= { hde3000c01v1Entry 43 }

		-- 1.3.6.1.4.1.10106.3.101291.1.1.45
		hde3000c01v1Grp1P1B OBJECT-TYPE
			SYNTAX AudioMxInput1
			MAX-ACCESS read-write
			STATUS current
			DESCRIPTION
				"Allows selecting the audio embedded in group 1 pair 1"
		::= { hde3000c01v1Entry 45 }

		-- 1.3.6.1.4.1.10106.3.101291.1.1.47
		hde3000c01v1Grp2P0B OBJECT-TYPE
			SYNTAX AudioMxInput1
			MAX-ACCESS read-write
			STATUS current
			DESCRIPTION
				"Allows selecting the audio embedded in group 2 pair 0"
		::= { hde3000c01v1Entry 47 }

		-- 1.3.6.1.4.1.10106.3.101291.1.1.49
		hde3000c01v1Grp2P1B OBJECT-TYPE
			SYNTAX AudioMxInput1
			MAX-ACCESS read-write
			STATUS current
			DESCRIPTION
				"Allows selecting the audio embedded in group 2 pair 1"
		::= { hde3000c01v1Entry 49 }

		-- 1.3.6.1.4.1.10106.3.101291.1.1.51
		hde3000c01v1Grp3P0B OBJECT-TYPE
			SYNTAX AudioMxInput1
			MAX-ACCESS read-write
			STATUS current
			DESCRIPTION
				"Allows selecting the audio embedded in group 3 pair 0"
		::= { hde3000c01v1Entry 51 }

		-- 1.3.6.1.4.1.10106.3.101291.1.1.53
		hde3000c01v1Grp3P1B OBJECT-TYPE
			SYNTAX AudioMxInput1
			MAX-ACCESS read-write
			STATUS current
			DESCRIPTION
				"Allows selecting the audio embedded in group 3 pair 1"
		::= { hde3000c01v1Entry 53 }

		-- 1.3.6.1.4.1.10106.3.101291.1.1.55
		hde3000c01v1Grp4P0B OBJECT-TYPE
			SYNTAX AudioMxInput1
			MAX-ACCESS read-write
			STATUS current
			DESCRIPTION
				"Allows selecting the audio embedded in group 4 pair 0"
		::= { hde3000c01v1Entry 55 }

		-- 1.3.6.1.4.1.10106.3.101291.1.1.57
		hde3000c01v1Grp4P1B OBJECT-TYPE
			SYNTAX AudioMxInput1
			MAX-ACCESS read-write
			STATUS current
			DESCRIPTION
				"Allows selecting the audio embedded in group 4 pair 1"
		::= { hde3000c01v1Entry 57 }

		-- 1.3.6.1.4.1.10106.3.101291.1.1.59
		hde3000c01v1Aes1A OBJECT-TYPE
			SYNTAX AudioMxInput2
			MAX-ACCESS read-write
			STATUS current
			DESCRIPTION
				"Allows selecting the audio deembedded in AES1"
		::= { hde3000c01v1Entry 59 }

		-- 1.3.6.1.4.1.10106.3.101291.1.1.61
		hde3000c01v1Aes2A OBJECT-TYPE
			SYNTAX AudioMxInput2
			MAX-ACCESS read-write
			STATUS current
			DESCRIPTION
				"Allows selecting the audio deembedded in AES2"
		::= { hde3000c01v1Entry 61 }

		-- 1.3.6.1.4.1.10106.3.101291.1.1.63
		hde3000c01v1Aes3A OBJECT-TYPE
			SYNTAX AudioMxInput2
			MAX-ACCESS read-write
			STATUS current
			DESCRIPTION
				"Allows selecting the audio deembedded in AES3"
		::= { hde3000c01v1Entry 63 }

		-- 1.3.6.1.4.1.10106.3.101291.1.1.65
		hde3000c01v1Aes4A OBJECT-TYPE
			SYNTAX AudioMxInput2
			MAX-ACCESS read-write
			STATUS current
			DESCRIPTION
				"Allows selecting the audio deembedded in AES4"
		::= { hde3000c01v1Entry 65 }

		-- 1.3.6.1.4.1.10106.3.101291.1.1.67
		hde3000c01v1Aes1B OBJECT-TYPE
			SYNTAX AudioMxInput2
			MAX-ACCESS read-write
			STATUS current
			DESCRIPTION
				"Allows selecting the audio deembedded in AES1"
		::= { hde3000c01v1Entry 67 }

		-- 1.3.6.1.4.1.10106.3.101291.1.1.69
		hde3000c01v1Aes2B OBJECT-TYPE
			SYNTAX AudioMxInput2
			MAX-ACCESS read-write
			STATUS current
			DESCRIPTION
				"Allows selecting the audio deembedded in AES2"
		::= { hde3000c01v1Entry 69 }

		-- 1.3.6.1.4.1.10106.3.101291.1.1.71
		hde3000c01v1Aes3B OBJECT-TYPE
			SYNTAX AudioMxInput2
			MAX-ACCESS read-write
			STATUS current
			DESCRIPTION
				"Allows selecting the audio deembedded in AES3"
		::= { hde3000c01v1Entry 71 }

		-- 1.3.6.1.4.1.10106.3.101291.1.1.73
		hde3000c01v1Aes4B OBJECT-TYPE
			SYNTAX AudioMxInput2
			MAX-ACCESS read-write
			STATUS current
			DESCRIPTION
				"Allows selecting the audio deembedded in AES4"
		::= { hde3000c01v1Entry 73 }

		-- 1.3.6.1.4.1.10106.3.101291.1.1.75
		hde3000c01v1OvldLevel OBJECT-TYPE
			SYNTAX LevelDbfs4
			MAX-ACCESS read-write
			STATUS current
			DESCRIPTION
				"Allows adjusting the threshold level for the overload detector"
		::= { hde3000c01v1Entry 75 }

		-- 1.3.6.1.4.1.10106.3.101291.1.1.77
		hde3000c01v1SilenceLevel OBJECT-TYPE
			SYNTAX LevelDbfs3
			MAX-ACCESS read-write
			STATUS current
			DESCRIPTION
				"Allows adjusting the threshold level for the silence detector"
		::= { hde3000c01v1Entry 77 }

		-- 1.3.6.1.4.1.10106.3.101291.1.1.79
		hde3000c01v1SilenceTime OBJECT-TYPE
			SYNTAX TimeS2
			MAX-ACCESS read-write
			STATUS current
			DESCRIPTION
				"Allows adjusting the silence time"
		::= { hde3000c01v1Entry 79 }

		-- 1.3.6.1.4.1.10106.3.101291.1.1.81
		hde3000c01v1DelayMode OBJECT-TYPE
			SYNTAX Bit0Out1In
			MAX-ACCESS read-write
			STATUS current
			DESCRIPTION
				"Allows selecting the delay module location"
		::= { hde3000c01v1Entry 81 }

		-- 1.3.6.1.4.1.10106.3.101291.1.1.83
		hde3000c01v1DelaySteps OBJECT-TYPE
			SYNTAX TimeX1Ms
			MAX-ACCESS read-write
			STATUS current
			DESCRIPTION
				"Allows adjusting the delay step for all delay controls"
		::= { hde3000c01v1Entry 83 }

		-- 1.3.6.1.4.1.10106.3.101291.1.1.85
		hde3000c01v1Grp1P0AGain OBJECT-TYPE
			SYNTAX Gain24dbMute
			MAX-ACCESS read-write
			STATUS current
			DESCRIPTION
				"Group 1 pair 0 gain"
		::= { hde3000c01v1Entry 85 }

		-- 1.3.6.1.4.1.10106.3.101291.1.1.87
		hde3000c01v1Grp1P1AGain OBJECT-TYPE
			SYNTAX Gain24dbMute
			MAX-ACCESS read-write
			STATUS current
			DESCRIPTION
				"Group 1 pair 1 gain"
		::= { hde3000c01v1Entry 87 }

		-- 1.3.6.1.4.1.10106.3.101291.1.1.89
		hde3000c01v1Grp2P0AGain OBJECT-TYPE
			SYNTAX Gain24dbMute
			MAX-ACCESS read-write
			STATUS current
			DESCRIPTION
				"Group 2 pair 0 gain"
		::= { hde3000c01v1Entry 89 }

		-- 1.3.6.1.4.1.10106.3.101291.1.1.91
		hde3000c01v1Grp2P1AGain OBJECT-TYPE
			SYNTAX Gain24dbMute
			MAX-ACCESS read-write
			STATUS current
			DESCRIPTION
				"Group 2 pair 1 gain"
		::= { hde3000c01v1Entry 91 }

		-- 1.3.6.1.4.1.10106.3.101291.1.1.93
		hde3000c01v1Grp3P0AGain OBJECT-TYPE
			SYNTAX Gain24dbMute
			MAX-ACCESS read-write
			STATUS current
			DESCRIPTION
				"Group 3 pair 0 gain"
		::= { hde3000c01v1Entry 93 }

		-- 1.3.6.1.4.1.10106.3.101291.1.1.95
		hde3000c01v1Grp3P1AGain OBJECT-TYPE
			SYNTAX Gain24dbMute
			MAX-ACCESS read-write
			STATUS current
			DESCRIPTION
				"Group 3 pair 1 gain"
		::= { hde3000c01v1Entry 95 }

		-- 1.3.6.1.4.1.10106.3.101291.1.1.97
		hde3000c01v1Grp4P0AGain OBJECT-TYPE
			SYNTAX Gain24dbMute
			MAX-ACCESS read-write
			STATUS current
			DESCRIPTION
				"Group 4 pair 0 gain"
		::= { hde3000c01v1Entry 97 }

		-- 1.3.6.1.4.1.10106.3.101291.1.1.99
		hde3000c01v1Grp4P1AGain OBJECT-TYPE
			SYNTAX Gain24dbMute
			MAX-ACCESS read-write
			STATUS current
			DESCRIPTION
				"Group 4 pair 1 gain"
		::= { hde3000c01v1Entry 99 }

		-- 1.3.6.1.4.1.10106.3.101291.1.1.101
		hde3000c01v1Grp1P0BGain OBJECT-TYPE
			SYNTAX Gain24dbMute
			MAX-ACCESS read-write
			STATUS current
			DESCRIPTION
				"Group 1 pair 0 gain"
		::= { hde3000c01v1Entry 101 }

		-- 1.3.6.1.4.1.10106.3.101291.1.1.103
		hde3000c01v1Grp1P1BGain OBJECT-TYPE
			SYNTAX Gain24dbMute
			MAX-ACCESS read-write
			STATUS current
			DESCRIPTION
				"Group 1 pair 1 gain"
		::= { hde3000c01v1Entry 103 }

		-- 1.3.6.1.4.1.10106.3.101291.1.1.105
		hde3000c01v1Grp2P0BGain OBJECT-TYPE
			SYNTAX Gain24dbMute
			MAX-ACCESS read-write
			STATUS current
			DESCRIPTION
				"Group 2 pair 0 gain"
		::= { hde3000c01v1Entry 105 }

		-- 1.3.6.1.4.1.10106.3.101291.1.1.107
		hde3000c01v1Grp2P1BGain OBJECT-TYPE
			SYNTAX Gain24dbMute
			MAX-ACCESS read-write
			STATUS current
			DESCRIPTION
				"Group 2 pair 1 gain"
		::= { hde3000c01v1Entry 107 }

		-- 1.3.6.1.4.1.10106.3.101291.1.1.109
		hde3000c01v1Grp3P0BGain OBJECT-TYPE
			SYNTAX Gain24dbMute
			MAX-ACCESS read-write
			STATUS current
			DESCRIPTION
				"Group 3 pair 0 gain"
		::= { hde3000c01v1Entry 109 }

		-- 1.3.6.1.4.1.10106.3.101291.1.1.111
		hde3000c01v1Grp3P1BGain OBJECT-TYPE
			SYNTAX Gain24dbMute
			MAX-ACCESS read-write
			STATUS current
			DESCRIPTION
				"Group 3 pair 1 gain"
		::= { hde3000c01v1Entry 111 }

		-- 1.3.6.1.4.1.10106.3.101291.1.1.113
		hde3000c01v1Grp4P0BGain OBJECT-TYPE
			SYNTAX Gain24dbMute
			MAX-ACCESS read-write
			STATUS current
			DESCRIPTION
				"Group 4 pair 0 gain"
		::= { hde3000c01v1Entry 113 }

		-- 1.3.6.1.4.1.10106.3.101291.1.1.115
		hde3000c01v1Grp4P1BGain OBJECT-TYPE
			SYNTAX Gain24dbMute
			MAX-ACCESS read-write
			STATUS current
			DESCRIPTION
				"Group 4 pair 1 gain"
		::= { hde3000c01v1Entry 115 }

		-- 1.3.6.1.4.1.10106.3.101291.1.1.117
		hde3000c01v1Aes1AGain OBJECT-TYPE
			SYNTAX Gain24dbMute
			MAX-ACCESS read-write
			STATUS current
			DESCRIPTION
				"AES1 output gain"
		::= { hde3000c01v1Entry 117 }

		-- 1.3.6.1.4.1.10106.3.101291.1.1.119
		hde3000c01v1Aes2AGain OBJECT-TYPE
			SYNTAX Gain24dbMute
			MAX-ACCESS read-write
			STATUS current
			DESCRIPTION
				"AES2 output  gain"
		::= { hde3000c01v1Entry 119 }

		-- 1.3.6.1.4.1.10106.3.101291.1.1.121
		hde3000c01v1Aes3AGain OBJECT-TYPE
			SYNTAX Gain24dbMute
			MAX-ACCESS read-write
			STATUS current
			DESCRIPTION
				"AES3  output gain"
		::= { hde3000c01v1Entry 121 }

		-- 1.3.6.1.4.1.10106.3.101291.1.1.123
		hde3000c01v1Aes4AGain OBJECT-TYPE
			SYNTAX Gain24dbMute
			MAX-ACCESS read-write
			STATUS current
			DESCRIPTION
				"AES4  output gain"
		::= { hde3000c01v1Entry 123 }

		-- 1.3.6.1.4.1.10106.3.101291.1.1.125
		hde3000c01v1Aes1BGain OBJECT-TYPE
			SYNTAX Gain24dbMute
			MAX-ACCESS read-write
			STATUS current
			DESCRIPTION
				"AES1 output  gain"
		::= { hde3000c01v1Entry 125 }

		-- 1.3.6.1.4.1.10106.3.101291.1.1.127
		hde3000c01v1Aes2BGain OBJECT-TYPE
			SYNTAX Gain24dbMute
			MAX-ACCESS read-write
			STATUS current
			DESCRIPTION
				"AES2  output gain"
		::= { hde3000c01v1Entry 127 }

		-- 1.3.6.1.4.1.10106.3.101291.1.1.129
		hde3000c01v1Aes3BGain OBJECT-TYPE
			SYNTAX Gain24dbMute
			MAX-ACCESS read-write
			STATUS current
			DESCRIPTION
				"AES3  output gain"
		::= { hde3000c01v1Entry 129 }

		-- 1.3.6.1.4.1.10106.3.101291.1.1.131
		hde3000c01v1Aes4BGain OBJECT-TYPE
			SYNTAX Gain24dbMute
			MAX-ACCESS read-write
			STATUS current
			DESCRIPTION
				"AES4  output gain"
		::= { hde3000c01v1Entry 131 }

		-- 1.3.6.1.4.1.10106.3.101291.1.1.133
		hde3000c01v1Grp1P0ADelay OBJECT-TYPE
			SYNTAX Uint8
			MAX-ACCESS read-write
			STATUS current
			DESCRIPTION
				"Group 1 pair 0 delay"
		::= { hde3000c01v1Entry 133 }

		-- 1.3.6.1.4.1.10106.3.101291.1.1.135
		hde3000c01v1Grp1P1ADelay OBJECT-TYPE
			SYNTAX Uint8
			MAX-ACCESS read-write
			STATUS current
			DESCRIPTION
				"Group 1 pair 1 delay"
		::= { hde3000c01v1Entry 135 }

		-- 1.3.6.1.4.1.10106.3.101291.1.1.137
		hde3000c01v1Grp2P0ADelay OBJECT-TYPE
			SYNTAX Uint8
			MAX-ACCESS read-write
			STATUS current
			DESCRIPTION
				"Group 2 pair 0 delay"
		::= { hde3000c01v1Entry 137 }

		-- 1.3.6.1.4.1.10106.3.101291.1.1.139
		hde3000c01v1Grp2P1ADelay OBJECT-TYPE
			SYNTAX Uint8
			MAX-ACCESS read-write
			STATUS current
			DESCRIPTION
				"Group 2 pair 1 delay"
		::= { hde3000c01v1Entry 139 }

		-- 1.3.6.1.4.1.10106.3.101291.1.1.141
		hde3000c01v1Grp3P0ADelay OBJECT-TYPE
			SYNTAX Uint8
			MAX-ACCESS read-write
			STATUS current
			DESCRIPTION
				"Group 3 pair 0 delay"
		::= { hde3000c01v1Entry 141 }

		-- 1.3.6.1.4.1.10106.3.101291.1.1.143
		hde3000c01v1Grp3P1ADelay OBJECT-TYPE
			SYNTAX Uint8
			MAX-ACCESS read-write
			STATUS current
			DESCRIPTION
				"Group 3 pair 1 delay"
		::= { hde3000c01v1Entry 143 }

		-- 1.3.6.1.4.1.10106.3.101291.1.1.145
		hde3000c01v1Grp4P0ADelay OBJECT-TYPE
			SYNTAX Uint8
			MAX-ACCESS read-write
			STATUS current
			DESCRIPTION
				"Group 4 pair 0 delay"
		::= { hde3000c01v1Entry 145 }

		-- 1.3.6.1.4.1.10106.3.101291.1.1.147
		hde3000c01v1Grp4P1ADelay OBJECT-TYPE
			SYNTAX Uint8
			MAX-ACCESS read-write
			STATUS current
			DESCRIPTION
				"Group 4 pair 1 delay"
		::= { hde3000c01v1Entry 147 }

		-- 1.3.6.1.4.1.10106.3.101291.1.1.149
		hde3000c01v1Grp1P0BDelay OBJECT-TYPE
			SYNTAX Uint8
			MAX-ACCESS read-write
			STATUS current
			DESCRIPTION
				"Group 1 pair 0 delay"
		::= { hde3000c01v1Entry 149 }

		-- 1.3.6.1.4.1.10106.3.101291.1.1.151
		hde3000c01v1Grp1P1BDelay OBJECT-TYPE
			SYNTAX Uint8
			MAX-ACCESS read-write
			STATUS current
			DESCRIPTION
				"Group 1 pair 1 delay"
		::= { hde3000c01v1Entry 151 }

		-- 1.3.6.1.4.1.10106.3.101291.1.1.153
		hde3000c01v1Grp2P0BDelay OBJECT-TYPE
			SYNTAX Uint8
			MAX-ACCESS read-write
			STATUS current
			DESCRIPTION
				"Group 2 pair 0 delay"
		::= { hde3000c01v1Entry 153 }

		-- 1.3.6.1.4.1.10106.3.101291.1.1.155
		hde3000c01v1Grp2P1BDelay OBJECT-TYPE
			SYNTAX Uint8
			MAX-ACCESS read-write
			STATUS current
			DESCRIPTION
				"Group 2 pair 1 delay"
		::= { hde3000c01v1Entry 155 }

		-- 1.3.6.1.4.1.10106.3.101291.1.1.157
		hde3000c01v1Grp3P0BDelay OBJECT-TYPE
			SYNTAX Uint8
			MAX-ACCESS read-write
			STATUS current
			DESCRIPTION
				"Group 3 pair 0 delay"
		::= { hde3000c01v1Entry 157 }

		-- 1.3.6.1.4.1.10106.3.101291.1.1.159
		hde3000c01v1Grp3P1BDelay OBJECT-TYPE
			SYNTAX Uint8
			MAX-ACCESS read-write
			STATUS current
			DESCRIPTION
				"Group 3 pair 1 delay"
		::= { hde3000c01v1Entry 159 }

		-- 1.3.6.1.4.1.10106.3.101291.1.1.161
		hde3000c01v1Grp4P0BDelay OBJECT-TYPE
			SYNTAX Uint8
			MAX-ACCESS read-write
			STATUS current
			DESCRIPTION
				"Group 4 pair 0 delay"
		::= { hde3000c01v1Entry 161 }

		-- 1.3.6.1.4.1.10106.3.101291.1.1.163
		hde3000c01v1Grp4P1BDelay OBJECT-TYPE
			SYNTAX Uint8
			MAX-ACCESS read-write
			STATUS current
			DESCRIPTION
				"Group 4 pair 1 delay"
		::= { hde3000c01v1Entry 163 }

		-- 1.3.6.1.4.1.10106.3.101291.1.1.165
		hde3000c01v1Aes1ADelay OBJECT-TYPE
			SYNTAX Uint8
			MAX-ACCESS read-write
			STATUS current
			DESCRIPTION
				"AES1 delay"
		::= { hde3000c01v1Entry 165 }

		-- 1.3.6.1.4.1.10106.3.101291.1.1.167
		hde3000c01v1Aes2ADelay OBJECT-TYPE
			SYNTAX Uint8
			MAX-ACCESS read-write
			STATUS current
			DESCRIPTION
				"AES2 delay"
		::= { hde3000c01v1Entry 167 }

		-- 1.3.6.1.4.1.10106.3.101291.1.1.169
		hde3000c01v1Aes3ADelay OBJECT-TYPE
			SYNTAX Uint8
			MAX-ACCESS read-write
			STATUS current
			DESCRIPTION
				"AES3 delay"
		::= { hde3000c01v1Entry 169 }

		-- 1.3.6.1.4.1.10106.3.101291.1.1.171
		hde3000c01v1Aes4ADelay OBJECT-TYPE
			SYNTAX Uint8
			MAX-ACCESS read-write
			STATUS current
			DESCRIPTION
				"AES4 delay"
		::= { hde3000c01v1Entry 171 }

		-- 1.3.6.1.4.1.10106.3.101291.1.1.173
		hde3000c01v1Aes1BDelay OBJECT-TYPE
			SYNTAX Uint8
			MAX-ACCESS read-write
			STATUS current
			DESCRIPTION
				"AES1 delay"
		::= { hde3000c01v1Entry 173 }

		-- 1.3.6.1.4.1.10106.3.101291.1.1.175
		hde3000c01v1Aes2BDelay OBJECT-TYPE
			SYNTAX Uint8
			MAX-ACCESS read-write
			STATUS current
			DESCRIPTION
				"AES2 delay"
		::= { hde3000c01v1Entry 175 }

		-- 1.3.6.1.4.1.10106.3.101291.1.1.177
		hde3000c01v1Aes3BDelay OBJECT-TYPE
			SYNTAX Uint8
			MAX-ACCESS read-write
			STATUS current
			DESCRIPTION
				"AES3 delay"
		::= { hde3000c01v1Entry 177 }

		-- 1.3.6.1.4.1.10106.3.101291.1.1.179
		hde3000c01v1Aes4BDelay OBJECT-TYPE
			SYNTAX Uint8
			MAX-ACCESS read-write
			STATUS current
			DESCRIPTION
				"AES4 delay"
		::= { hde3000c01v1Entry 179 }

		-- 1.3.6.1.4.1.10106.3.101291.1.1.181
		hde3000c01v1NoSignalA OBJECT-TYPE
			SYNTAX BitFail
			MAX-ACCESS read-only
			STATUS current
			DESCRIPTION
				"There is no SDI signal or the format is not supported"
		::= { hde3000c01v1Entry 181 }

		-- 1.3.6.1.4.1.10106.3.101291.1.1.182
		hde3000c01v1NoSignalATrapEnable OBJECT-TYPE
			SYNTAX AlarmEnable
			MAX-ACCESS read-write
			STATUS current
			DESCRIPTION
				"There is no SDI signal or the format is not supported Trap Enable"
		::= { hde3000c01v1Entry 182 }

		-- 1.3.6.1.4.1.10106.3.101291.1.1.183
		hde3000c01v1UnlockA OBJECT-TYPE
			SYNTAX BitFail
			MAX-ACCESS read-only
			STATUS current
			DESCRIPTION
				"Indicates signal unlock fail"
		::= { hde3000c01v1Entry 183 }

		-- 1.3.6.1.4.1.10106.3.101291.1.1.184
		hde3000c01v1UnlockATrapEnable OBJECT-TYPE
			SYNTAX AlarmEnable
			MAX-ACCESS read-write
			STATUS current
			DESCRIPTION
				"Indicates signal unlock fail Trap Enable"
		::= { hde3000c01v1Entry 184 }

		-- 1.3.6.1.4.1.10106.3.101291.1.1.185
		hde3000c01v1EdhErrorA OBJECT-TYPE
			SYNTAX BitFail
			MAX-ACCESS read-only
			STATUS current
			DESCRIPTION
				"There are EDH/CRC errors on SDI signal"
		::= { hde3000c01v1Entry 185 }

		-- 1.3.6.1.4.1.10106.3.101291.1.1.186
		hde3000c01v1EdhErrorATrapEnable OBJECT-TYPE
			SYNTAX AlarmEnable
			MAX-ACCESS read-write
			STATUS current
			DESCRIPTION
				"There are EDH/CRC errors on SDI signal Trap Enable"
		::= { hde3000c01v1Entry 186 }

		-- 1.3.6.1.4.1.10106.3.101291.1.1.187
		hde3000c01v1AesFailA OBJECT-TYPE
			SYNTAX BitFail
			MAX-ACCESS read-only
			STATUS current
			DESCRIPTION
				"There is no valid audio in AES inputs"
		::= { hde3000c01v1Entry 187 }

		-- 1.3.6.1.4.1.10106.3.101291.1.1.188
		hde3000c01v1AesFailATrapEnable OBJECT-TYPE
			SYNTAX AlarmEnable
			MAX-ACCESS read-write
			STATUS current
			DESCRIPTION
				"There is no valid audio in AES inputs Trap Enable"
		::= { hde3000c01v1Entry 188 }

		-- 1.3.6.1.4.1.10106.3.101291.1.1.189
		hde3000c01v1DeemFailA OBJECT-TYPE
			SYNTAX BitFail
			MAX-ACCESS read-only
			STATUS current
			DESCRIPTION
				"There is no valid deembedded audio"
		::= { hde3000c01v1Entry 189 }

		-- 1.3.6.1.4.1.10106.3.101291.1.1.190
		hde3000c01v1DeemFailATrapEnable OBJECT-TYPE
			SYNTAX AlarmEnable
			MAX-ACCESS read-write
			STATUS current
			DESCRIPTION
				"There is no valid deembedded audio Trap Enable"
		::= { hde3000c01v1Entry 190 }

		-- 1.3.6.1.4.1.10106.3.101291.1.1.191
		hde3000c01v1AesOvlA OBJECT-TYPE
			SYNTAX BitFail
			MAX-ACCESS read-only
			STATUS current
			DESCRIPTION
				"There is overload or silence in AES outputs"
		::= { hde3000c01v1Entry 191 }

		-- 1.3.6.1.4.1.10106.3.101291.1.1.192
		hde3000c01v1AesOvlATrapEnable OBJECT-TYPE
			SYNTAX AlarmEnable
			MAX-ACCESS read-write
			STATUS current
			DESCRIPTION
				"There is overload or silence in AES outputs Trap Enable"
		::= { hde3000c01v1Entry 192 }

		-- 1.3.6.1.4.1.10106.3.101291.1.1.193
		hde3000c01v1DeemOvlA OBJECT-TYPE
			SYNTAX BitFail
			MAX-ACCESS read-only
			STATUS current
			DESCRIPTION
				"There is overload or silence in embed audio"
		::= { hde3000c01v1Entry 193 }

		-- 1.3.6.1.4.1.10106.3.101291.1.1.194
		hde3000c01v1DeemOvlATrapEnable OBJECT-TYPE
			SYNTAX AlarmEnable
			MAX-ACCESS read-write
			STATUS current
			DESCRIPTION
				"There is overload or silence in embed audio Trap Enable"
		::= { hde3000c01v1Entry 194 }

		-- 1.3.6.1.4.1.10106.3.101291.1.1.195
		hde3000c01v1FormatA OBJECT-TYPE
			SYNTAX SdiHd3gFmt3
			MAX-ACCESS read-only
			STATUS current
			DESCRIPTION
				"Indicates the SDI transmited signal format"
		::= { hde3000c01v1Entry 195 }

		-- 1.3.6.1.4.1.10106.3.101291.1.1.197
		hde3000c01v1NoSignalB OBJECT-TYPE
			SYNTAX BitFail
			MAX-ACCESS read-only
			STATUS current
			DESCRIPTION
				"There is no SDI signal or the format is not supported"
		::= { hde3000c01v1Entry 197 }

		-- 1.3.6.1.4.1.10106.3.101291.1.1.198
		hde3000c01v1NoSignalBTrapEnable OBJECT-TYPE
			SYNTAX AlarmEnable
			MAX-ACCESS read-write
			STATUS current
			DESCRIPTION
				"There is no SDI signal or the format is not supported Trap Enable"
		::= { hde3000c01v1Entry 198 }

		-- 1.3.6.1.4.1.10106.3.101291.1.1.199
		hde3000c01v1UnlockB OBJECT-TYPE
			SYNTAX BitFail
			MAX-ACCESS read-only
			STATUS current
			DESCRIPTION
				"Indicates signal unlock fail"
		::= { hde3000c01v1Entry 199 }

		-- 1.3.6.1.4.1.10106.3.101291.1.1.200
		hde3000c01v1UnlockBTrapEnable OBJECT-TYPE
			SYNTAX AlarmEnable
			MAX-ACCESS read-write
			STATUS current
			DESCRIPTION
				"Indicates signal unlock fail Trap Enable"
		::= { hde3000c01v1Entry 200 }

		-- 1.3.6.1.4.1.10106.3.101291.1.1.201
		hde3000c01v1EdhErrorB OBJECT-TYPE
			SYNTAX BitFail
			MAX-ACCESS read-only
			STATUS current
			DESCRIPTION
				"There are EDH/CRC errors on SDI signal"
		::= { hde3000c01v1Entry 201 }

		-- 1.3.6.1.4.1.10106.3.101291.1.1.202
		hde3000c01v1EdhErrorBTrapEnable OBJECT-TYPE
			SYNTAX AlarmEnable
			MAX-ACCESS read-write
			STATUS current
			DESCRIPTION
				"There are EDH/CRC errors on SDI signal Trap Enable"
		::= { hde3000c01v1Entry 202 }

		-- 1.3.6.1.4.1.10106.3.101291.1.1.203
		hde3000c01v1AesFailB OBJECT-TYPE
			SYNTAX BitFail
			MAX-ACCESS read-only
			STATUS current
			DESCRIPTION
				"There is no valid audio in AES inputs"
		::= { hde3000c01v1Entry 203 }

		-- 1.3.6.1.4.1.10106.3.101291.1.1.204
		hde3000c01v1AesFailBTrapEnable OBJECT-TYPE
			SYNTAX AlarmEnable
			MAX-ACCESS read-write
			STATUS current
			DESCRIPTION
				"There is no valid audio in AES inputs Trap Enable"
		::= { hde3000c01v1Entry 204 }

		-- 1.3.6.1.4.1.10106.3.101291.1.1.205
		hde3000c01v1DeemFailB OBJECT-TYPE
			SYNTAX BitFail
			MAX-ACCESS read-only
			STATUS current
			DESCRIPTION
				"There is no valid deembedded audio"
		::= { hde3000c01v1Entry 205 }

		-- 1.3.6.1.4.1.10106.3.101291.1.1.206
		hde3000c01v1DeemFailBTrapEnable OBJECT-TYPE
			SYNTAX AlarmEnable
			MAX-ACCESS read-write
			STATUS current
			DESCRIPTION
				"There is no valid deembedded audio Trap Enable"
		::= { hde3000c01v1Entry 206 }

		-- 1.3.6.1.4.1.10106.3.101291.1.1.207
		hde3000c01v1AesOvlB OBJECT-TYPE
			SYNTAX BitFail
			MAX-ACCESS read-only
			STATUS current
			DESCRIPTION
				"There is overload or silence in AES outputs"
		::= { hde3000c01v1Entry 207 }

		-- 1.3.6.1.4.1.10106.3.101291.1.1.208
		hde3000c01v1AesOvlBTrapEnable OBJECT-TYPE
			SYNTAX AlarmEnable
			MAX-ACCESS read-write
			STATUS current
			DESCRIPTION
				"There is overload or silence in AES outputs Trap Enable"
		::= { hde3000c01v1Entry 208 }

		-- 1.3.6.1.4.1.10106.3.101291.1.1.209
		hde3000c01v1DeemOvlB OBJECT-TYPE
			SYNTAX BitFail
			MAX-ACCESS read-only
			STATUS current
			DESCRIPTION
				"There is overload or silence in embed audio"
		::= { hde3000c01v1Entry 209 }

		-- 1.3.6.1.4.1.10106.3.101291.1.1.210
		hde3000c01v1DeemOvlBTrapEnable OBJECT-TYPE
			SYNTAX AlarmEnable
			MAX-ACCESS read-write
			STATUS current
			DESCRIPTION
				"There is overload or silence in embed audio Trap Enable"
		::= { hde3000c01v1Entry 210 }

		-- 1.3.6.1.4.1.10106.3.101291.1.1.211
		hde3000c01v1FormatB OBJECT-TYPE
			SYNTAX SdiHd3gFmt3
			MAX-ACCESS read-only
			STATUS current
			DESCRIPTION
				"Indicates the SDI transmited signal format"
		::= { hde3000c01v1Entry 211 }

		-- 1.3.6.1.4.1.10106.3.101291.1.1.213
		hde3000c01v1SerialNo OBJECT-TYPE
			SYNTAX SerialNo
			MAX-ACCESS read-only
			STATUS current
			DESCRIPTION
				"Serial number"
		::= { hde3000c01v1Entry 213 }

		-- 1.3.6.1.4.1.10106.3.101291.1.1.215
		hde3000c01v1CorteSelChB OBJECT-TYPE
			SYNTAX Bit0BlBit1Cut
			MAX-ACCESS read-write
			STATUS current
			DESCRIPTION
				"Selects the action to perform when the input signal is absent"
		::= { hde3000c01v1Entry 215 }

		-- 1.3.6.1.4.1.10106.3.359901
		hae3000c01v1 OBJECT IDENTIFIER ::= { albalaProducts 359901 }

		-- 1.3.6.1.4.1.10106.3.359901.1
		hae3000c01v1Table  OBJECT-TYPE
			SYNTAX SEQUENCE OF Hae3000c01v1Entry
			MAX-ACCESS not-accessible
			STATUS current
			DESCRIPTION
				"Module  HAE3000C01V1 Table"
			::= { hae3000c01v1 1 }

		-- 1.3.6.1.4.1.10106.3.359901.1.1
		hae3000c01v1Entry  OBJECT-TYPE
			SYNTAX Hae3000c01v1Entry
			MAX-ACCESS not-accessible
			STATUS current
			DESCRIPTION
				"Module HAE3000C01V1 Entry"
			INDEX { hae3000c01v1Index }
			::= { hae3000c01v1Table 1 }

			Hae3000c01v1Entry ::=
			SEQUENCE {
				hae3000c01v1Index
				ModuleIndex,
				hae3000c01v1RestorPreset
				PresetRestore,
				hae3000c01v1ActivePreset
				PresetActive,
				hae3000c01v1LoadPreset
				PresetLoad,
				hae3000c01v1SavePreset
				PresetSave,
				hae3000c01v1ClnGr1A
				Bit0No1Yes,
				hae3000c01v1ClnGr2A
				Bit0No1Yes,
				hae3000c01v1ClnGr3A
				Bit0No1Yes,
				hae3000c01v1ClnGr4A
				Bit0No1Yes,
				hae3000c01v1ClnGr1B
				Bit0No1Yes,
				hae3000c01v1ClnGr2B
				Bit0No1Yes,
				hae3000c01v1ClnGr3B
				Bit0No1Yes,
				hae3000c01v1ClnGr4B
				Bit0No1Yes,
				hae3000c01v1Grp1P0A
				AudioMxInput3,
				hae3000c01v1Grp1P1A
				AudioMxInput3,
				hae3000c01v1Grp2P0A
				AudioMxInput3,
				hae3000c01v1Grp2P1A
				AudioMxInput3,
				hae3000c01v1Grp3P0A
				AudioMxInput3,
				hae3000c01v1Grp3P1A
				AudioMxInput3,
				hae3000c01v1Grp4P0A
				AudioMxInput3,
				hae3000c01v1Grp4P1A
				AudioMxInput3,
				hae3000c01v1Grp1P0B
				AudioMxInput3,
				hae3000c01v1Grp1P1B
				AudioMxInput3,
				hae3000c01v1Grp2P0B
				AudioMxInput3,
				hae3000c01v1Grp2P1B
				AudioMxInput3,
				hae3000c01v1Grp3P0B
				AudioMxInput3,
				hae3000c01v1Grp3P1B
				AudioMxInput3,
				hae3000c01v1Grp4P0B
				AudioMxInput3,
				hae3000c01v1Grp4P1B
				AudioMxInput3,
				hae3000c01v1FullScaleLev
				Uint5,
				hae3000c01v1SamplingClkA
				HaeSampClk,
				hae3000c01v1SamplingClkB
				HaeSampClk,
				hae3000c01v1OvldLevel
				LevelDbfs4,
				hae3000c01v1SilenceLevel
				LevelDbfs3,
				hae3000c01v1SilenceTime
				TimeS2,
				hae3000c01v1DelayMode
				Bit0Out1In,
				hae3000c01v1DelaySteps
				TimeX1Ms,
				hae3000c01v1Grp1P0AGain
				Gain24dbMute,
				hae3000c01v1Grp1P1AGain
				Gain24dbMute,
				hae3000c01v1Grp2P0AGain
				Gain24dbMute,
				hae3000c01v1Grp2P1AGain
				Gain24dbMute,
				hae3000c01v1Grp3P0AGain
				Gain24dbMute,
				hae3000c01v1Grp3P1AGain
				Gain24dbMute,
				hae3000c01v1Grp4P0AGain
				Gain24dbMute,
				hae3000c01v1Grp4P1AGain
				Gain24dbMute,
				hae3000c01v1Grp1P0BGain
				Gain24dbMute,
				hae3000c01v1Grp1P1BGain
				Gain24dbMute,
				hae3000c01v1Grp2P0BGain
				Gain24dbMute,
				hae3000c01v1Grp2P1BGain
				Gain24dbMute,
				hae3000c01v1Grp3P0BGain
				Gain24dbMute,
				hae3000c01v1Grp3P1BGain
				Gain24dbMute,
				hae3000c01v1Grp4P0BGain
				Gain24dbMute,
				hae3000c01v1Grp4P1BGain
				Gain24dbMute,
				hae3000c01v1Grp1P0ADelay
				Uint8,
				hae3000c01v1Grp1P1ADelay
				Uint8,
				hae3000c01v1Grp2P0ADelay
				Uint8,
				hae3000c01v1Grp2P1ADelay
				Uint8,
				hae3000c01v1Grp3P0ADelay
				Uint8,
				hae3000c01v1Grp3P1ADelay
				Uint8,
				hae3000c01v1Grp4P0ADelay
				Uint8,
				hae3000c01v1Grp4P1ADelay
				Uint8,
				hae3000c01v1Grp1P0BDelay
				Uint8,
				hae3000c01v1Grp1P1BDelay
				Uint8,
				hae3000c01v1Grp2P0BDelay
				Uint8,
				hae3000c01v1Grp2P1BDelay
				Uint8,
				hae3000c01v1Grp3P0BDelay
				Uint8,
				hae3000c01v1Grp3P1BDelay
				Uint8,
				hae3000c01v1Grp4P0BDelay
				Uint8,
				hae3000c01v1Grp4P1BDelay
				Uint8,
				hae3000c01v1NoSignalA
				BitFail,
				hae3000c01v1NoSignalATrapEnable
				AlarmEnable,
				hae3000c01v1UnlockA
				BitFail,
				hae3000c01v1UnlockATrapEnable
				AlarmEnable,
				hae3000c01v1EdhErrorA
				BitFail,
				hae3000c01v1EdhErrorATrapEnable
				AlarmEnable,
				hae3000c01v1AesFailA
				BitFail,
				hae3000c01v1AesFailATrapEnable
				AlarmEnable,
				hae3000c01v1DeemFailA
				BitFail,
				hae3000c01v1DeemFailATrapEnable
				AlarmEnable,
				hae3000c01v1DeemOvlA
				BitFail,
				hae3000c01v1DeemOvlATrapEnable
				AlarmEnable,
				hae3000c01v1ClippingA
				BitFail,
				hae3000c01v1ClippingATrapEnable
				AlarmEnable,
				hae3000c01v1FormatA
				SdiHd3gFmt3,
				hae3000c01v1NoSignalB
				BitFail,
				hae3000c01v1NoSignalBTrapEnable
				AlarmEnable,
				hae3000c01v1UnlockB
				BitFail,
				hae3000c01v1UnlockBTrapEnable
				AlarmEnable,
				hae3000c01v1EdhErrorB
				BitFail,
				hae3000c01v1EdhErrorBTrapEnable
				AlarmEnable,
				hae3000c01v1AesFailB
				BitFail,
				hae3000c01v1AesFailBTrapEnable
				AlarmEnable,
				hae3000c01v1DeemFailB
				BitFail,
				hae3000c01v1DeemFailBTrapEnable
				AlarmEnable,
				hae3000c01v1DeemOvlB
				BitFail,
				hae3000c01v1DeemOvlBTrapEnable
				AlarmEnable,
				hae3000c01v1ClippingB
				BitFail,
				hae3000c01v1ClippingBTrapEnable
				AlarmEnable,
				hae3000c01v1FormatB
				SdiHd3gFmt3,
				hae3000c01v1SerialNo
				SerialNo,
				hae3000c01v1CorteSelChB
				Bit0BlBit1Cut
			 }

		-- 1.3.6.1.4.1.10106.3.101291.1.1.1
		hae3000c01v1Index OBJECT-TYPE
			SYNTAX ModuleIndex
			MAX-ACCESS read-only
			STATUS current
			DESCRIPTION
				"Index of HAE3000C01V1 Table"
		::= { hae3000c01v1Entry 1 }

		-- 1.3.6.1.4.1.10106.3.101291.1.1.3
		hae3000c01v1RestorPreset OBJECT-TYPE
			SYNTAX PresetRestore
			MAX-ACCESS read-write
			STATUS current
			DESCRIPTION
				"Allows restoring a factory preset"
		::= { hae3000c01v1Entry 3 }

		-- 1.3.6.1.4.1.10106.3.101291.1.1.5
		hae3000c01v1ActivePreset OBJECT-TYPE
			SYNTAX PresetActive
			MAX-ACCESS read-only
			STATUS current
			DESCRIPTION
				"Shows the active preset"
		::= { hae3000c01v1Entry 5 }

		-- 1.3.6.1.4.1.10106.3.101291.1.1.7
		hae3000c01v1LoadPreset OBJECT-TYPE
			SYNTAX PresetLoad
			MAX-ACCESS read-write
			STATUS current
			DESCRIPTION
				"Allows loading a preset"
		::= { hae3000c01v1Entry 7 }

		-- 1.3.6.1.4.1.10106.3.101291.1.1.9
		hae3000c01v1SavePreset OBJECT-TYPE
			SYNTAX PresetSave
			MAX-ACCESS read-write
			STATUS current
			DESCRIPTION
				"Allows saving a preset"
		::= { hae3000c01v1Entry 9 }

		-- 1.3.6.1.4.1.10106.3.101291.1.1.11
		hae3000c01v1ClnGr1A OBJECT-TYPE
			SYNTAX Bit0No1Yes
			MAX-ACCESS read-write
			STATUS current
			DESCRIPTION
				"Allows selecting if all the group 1 audio packets are deleted after deembedding"
		::= { hae3000c01v1Entry 11 }

		-- 1.3.6.1.4.1.10106.3.101291.1.1.13
		hae3000c01v1ClnGr2A OBJECT-TYPE
			SYNTAX Bit0No1Yes
			MAX-ACCESS read-write
			STATUS current
			DESCRIPTION
				"Allows selecting if all the group 2 audio packets are deleted after deembedding"
		::= { hae3000c01v1Entry 13 }

		-- 1.3.6.1.4.1.10106.3.101291.1.1.15
		hae3000c01v1ClnGr3A OBJECT-TYPE
			SYNTAX Bit0No1Yes
			MAX-ACCESS read-write
			STATUS current
			DESCRIPTION
				"Allows selecting if all the group 3 audio packets are deleted after deembedding"
		::= { hae3000c01v1Entry 15 }

		-- 1.3.6.1.4.1.10106.3.101291.1.1.17
		hae3000c01v1ClnGr4A OBJECT-TYPE
			SYNTAX Bit0No1Yes
			MAX-ACCESS read-write
			STATUS current
			DESCRIPTION
				"Allows selecting if all the group 4 audio packets are deleted after deembedding"
		::= { hae3000c01v1Entry 17 }

		-- 1.3.6.1.4.1.10106.3.101291.1.1.19
		hae3000c01v1ClnGr1B OBJECT-TYPE
			SYNTAX Bit0No1Yes
			MAX-ACCESS read-write
			STATUS current
			DESCRIPTION
				"Allows selecting if all the group 1 audio packets are deleted after deembedding"
		::= { hae3000c01v1Entry 19 }

		-- 1.3.6.1.4.1.10106.3.101291.1.1.21
		hae3000c01v1ClnGr2B OBJECT-TYPE
			SYNTAX Bit0No1Yes
			MAX-ACCESS read-write
			STATUS current
			DESCRIPTION
				"Allows selecting if all the group 2 audio packets are deleted after deembedding"
		::= { hae3000c01v1Entry 21 }

		-- 1.3.6.1.4.1.10106.3.101291.1.1.23
		hae3000c01v1ClnGr3B OBJECT-TYPE
			SYNTAX Bit0No1Yes
			MAX-ACCESS read-write
			STATUS current
			DESCRIPTION
				"Allows selecting if all the group 3 audio packets are deleted after deembedding"
		::= { hae3000c01v1Entry 23 }

		-- 1.3.6.1.4.1.10106.3.101291.1.1.25
		hae3000c01v1ClnGr4B OBJECT-TYPE
			SYNTAX Bit0No1Yes
			MAX-ACCESS read-write
			STATUS current
			DESCRIPTION
				"Allows selecting if all the group 4 audio packets are deleted after deembedding"
		::= { hae3000c01v1Entry 25 }

		-- 1.3.6.1.4.1.10106.3.101291.1.1.27
		hae3000c01v1Grp1P0A OBJECT-TYPE
			SYNTAX AudioMxInput3
			MAX-ACCESS read-write
			STATUS current
			DESCRIPTION
				"Allows selecting the audio embedded in group 1 pair 0"
		::= { hae3000c01v1Entry 27 }

		-- 1.3.6.1.4.1.10106.3.101291.1.1.29
		hae3000c01v1Grp1P1A OBJECT-TYPE
			SYNTAX AudioMxInput3
			MAX-ACCESS read-write
			STATUS current
			DESCRIPTION
				"Allows selecting the audio embedded in group 1 pair 1"
		::= { hae3000c01v1Entry 29 }

		-- 1.3.6.1.4.1.10106.3.101291.1.1.31
		hae3000c01v1Grp2P0A OBJECT-TYPE
			SYNTAX AudioMxInput3
			MAX-ACCESS read-write
			STATUS current
			DESCRIPTION
				"Allows selecting the audio embedded in group 2 pair 0"
		::= { hae3000c01v1Entry 31 }

		-- 1.3.6.1.4.1.10106.3.101291.1.1.33
		hae3000c01v1Grp2P1A OBJECT-TYPE
			SYNTAX AudioMxInput3
			MAX-ACCESS read-write
			STATUS current
			DESCRIPTION
				"Allows selecting the audio embedded in group 2 pair 1"
		::= { hae3000c01v1Entry 33 }

		-- 1.3.6.1.4.1.10106.3.101291.1.1.35
		hae3000c01v1Grp3P0A OBJECT-TYPE
			SYNTAX AudioMxInput3
			MAX-ACCESS read-write
			STATUS current
			DESCRIPTION
				"Allows selecting the audio embedded in group 3 pair 0"
		::= { hae3000c01v1Entry 35 }

		-- 1.3.6.1.4.1.10106.3.101291.1.1.37
		hae3000c01v1Grp3P1A OBJECT-TYPE
			SYNTAX AudioMxInput3
			MAX-ACCESS read-write
			STATUS current
			DESCRIPTION
				"Allows selecting the audio embedded in group 3 pair 1"
		::= { hae3000c01v1Entry 37 }

		-- 1.3.6.1.4.1.10106.3.101291.1.1.39
		hae3000c01v1Grp4P0A OBJECT-TYPE
			SYNTAX AudioMxInput3
			MAX-ACCESS read-write
			STATUS current
			DESCRIPTION
				"Allows selecting the audio embedded in group 4 pair 0"
		::= { hae3000c01v1Entry 39 }

		-- 1.3.6.1.4.1.10106.3.101291.1.1.41
		hae3000c01v1Grp4P1A OBJECT-TYPE
			SYNTAX AudioMxInput3
			MAX-ACCESS read-write
			STATUS current
			DESCRIPTION
				"Allows selecting the audio embedded in group 4 pair 1"
		::= { hae3000c01v1Entry 41 }

		-- 1.3.6.1.4.1.10106.3.101291.1.1.43
		hae3000c01v1Grp1P0B OBJECT-TYPE
			SYNTAX AudioMxInput3
			MAX-ACCESS read-write
			STATUS current
			DESCRIPTION
				"Allows selecting the audio embedded in group 1 pair 0"
		::= { hae3000c01v1Entry 43 }

		-- 1.3.6.1.4.1.10106.3.101291.1.1.45
		hae3000c01v1Grp1P1B OBJECT-TYPE
			SYNTAX AudioMxInput3
			MAX-ACCESS read-write
			STATUS current
			DESCRIPTION
				"Allows selecting the audio embedded in group 1 pair 1"
		::= { hae3000c01v1Entry 45 }

		-- 1.3.6.1.4.1.10106.3.101291.1.1.47
		hae3000c01v1Grp2P0B OBJECT-TYPE
			SYNTAX AudioMxInput3
			MAX-ACCESS read-write
			STATUS current
			DESCRIPTION
				"Allows selecting the audio embedded in group 2 pair 0"
		::= { hae3000c01v1Entry 47 }

		-- 1.3.6.1.4.1.10106.3.101291.1.1.49
		hae3000c01v1Grp2P1B OBJECT-TYPE
			SYNTAX AudioMxInput3
			MAX-ACCESS read-write
			STATUS current
			DESCRIPTION
				"Allows selecting the audio embedded in group 2 pair 1"
		::= { hae3000c01v1Entry 49 }

		-- 1.3.6.1.4.1.10106.3.101291.1.1.51
		hae3000c01v1Grp3P0B OBJECT-TYPE
			SYNTAX AudioMxInput3
			MAX-ACCESS read-write
			STATUS current
			DESCRIPTION
				"Allows selecting the audio embedded in group 3 pair 0"
		::= { hae3000c01v1Entry 51 }

		-- 1.3.6.1.4.1.10106.3.101291.1.1.53
		hae3000c01v1Grp3P1B OBJECT-TYPE
			SYNTAX AudioMxInput3
			MAX-ACCESS read-write
			STATUS current
			DESCRIPTION
				"Allows selecting the audio embedded in group 3 pair 1"
		::= { hae3000c01v1Entry 53 }

		-- 1.3.6.1.4.1.10106.3.101291.1.1.55
		hae3000c01v1Grp4P0B OBJECT-TYPE
			SYNTAX AudioMxInput3
			MAX-ACCESS read-write
			STATUS current
			DESCRIPTION
				"Allows selecting the audio embedded in group 4 pair 0"
		::= { hae3000c01v1Entry 55 }

		-- 1.3.6.1.4.1.10106.3.101291.1.1.57
		hae3000c01v1Grp4P1B OBJECT-TYPE
			SYNTAX AudioMxInput3
			MAX-ACCESS read-write
			STATUS current
			DESCRIPTION
				"Allows selecting the audio embedded in group 4 pair 1"
		::= { hae3000c01v1Entry 57 }

		-- 1.3.6.1.4.1.10106.3.101291.1.1.59
		hae3000c01v1FullScaleLev OBJECT-TYPE
			SYNTAX Uint5
			MAX-ACCESS read-write
			STATUS current
			DESCRIPTION
				"Full scale level"
		::= { hae3000c01v1Entry 59 }

		-- 1.3.6.1.4.1.10106.3.101291.1.1.61
		hae3000c01v1SamplingClkA OBJECT-TYPE
			SYNTAX HaeSampClk
			MAX-ACCESS read-write
			STATUS current
			DESCRIPTION
				"Sampling clock"
		::= { hae3000c01v1Entry 61 }

		-- 1.3.6.1.4.1.10106.3.101291.1.1.63
		hae3000c01v1SamplingClkB OBJECT-TYPE
			SYNTAX HaeSampClk
			MAX-ACCESS read-write
			STATUS current
			DESCRIPTION
				"Sampling clock"
		::= { hae3000c01v1Entry 63 }

		-- 1.3.6.1.4.1.10106.3.101291.1.1.65
		hae3000c01v1OvldLevel OBJECT-TYPE
			SYNTAX LevelDbfs4
			MAX-ACCESS read-write
			STATUS current
			DESCRIPTION
				"Allows adjusting the threshold level for the overload detector"
		::= { hae3000c01v1Entry 65 }

		-- 1.3.6.1.4.1.10106.3.101291.1.1.67
		hae3000c01v1SilenceLevel OBJECT-TYPE
			SYNTAX LevelDbfs3
			MAX-ACCESS read-write
			STATUS current
			DESCRIPTION
				"Allows adjusting the threshold level for the silence detector"
		::= { hae3000c01v1Entry 67 }

		-- 1.3.6.1.4.1.10106.3.101291.1.1.69
		hae3000c01v1SilenceTime OBJECT-TYPE
			SYNTAX TimeS2
			MAX-ACCESS read-write
			STATUS current
			DESCRIPTION
				"Allows adjusting the silence time"
		::= { hae3000c01v1Entry 69 }

		-- 1.3.6.1.4.1.10106.3.101291.1.1.71
		hae3000c01v1DelayMode OBJECT-TYPE
			SYNTAX Bit0Out1In
			MAX-ACCESS read-write
			STATUS current
			DESCRIPTION
				"Allows selecting the delay module location"
		::= { hae3000c01v1Entry 71 }

		-- 1.3.6.1.4.1.10106.3.101291.1.1.73
		hae3000c01v1DelaySteps OBJECT-TYPE
			SYNTAX TimeX1Ms
			MAX-ACCESS read-write
			STATUS current
			DESCRIPTION
				"Allows adjusting the delay step for all delay controls"
		::= { hae3000c01v1Entry 73 }

		-- 1.3.6.1.4.1.10106.3.101291.1.1.75
		hae3000c01v1Grp1P0AGain OBJECT-TYPE
			SYNTAX Gain24dbMute
			MAX-ACCESS read-write
			STATUS current
			DESCRIPTION
				"Group 1 pair 0 gain"
		::= { hae3000c01v1Entry 75 }

		-- 1.3.6.1.4.1.10106.3.101291.1.1.77
		hae3000c01v1Grp1P1AGain OBJECT-TYPE
			SYNTAX Gain24dbMute
			MAX-ACCESS read-write
			STATUS current
			DESCRIPTION
				"Group 1 pair 1 gain"
		::= { hae3000c01v1Entry 77 }

		-- 1.3.6.1.4.1.10106.3.101291.1.1.79
		hae3000c01v1Grp2P0AGain OBJECT-TYPE
			SYNTAX Gain24dbMute
			MAX-ACCESS read-write
			STATUS current
			DESCRIPTION
				"Group 2 pair 0 gain"
		::= { hae3000c01v1Entry 79 }

		-- 1.3.6.1.4.1.10106.3.101291.1.1.81
		hae3000c01v1Grp2P1AGain OBJECT-TYPE
			SYNTAX Gain24dbMute
			MAX-ACCESS read-write
			STATUS current
			DESCRIPTION
				"Group 2 pair 1 gain"
		::= { hae3000c01v1Entry 81 }

		-- 1.3.6.1.4.1.10106.3.101291.1.1.83
		hae3000c01v1Grp3P0AGain OBJECT-TYPE
			SYNTAX Gain24dbMute
			MAX-ACCESS read-write
			STATUS current
			DESCRIPTION
				"Group 3 pair 0 gain"
		::= { hae3000c01v1Entry 83 }

		-- 1.3.6.1.4.1.10106.3.101291.1.1.85
		hae3000c01v1Grp3P1AGain OBJECT-TYPE
			SYNTAX Gain24dbMute
			MAX-ACCESS read-write
			STATUS current
			DESCRIPTION
				"Group 3 pair 1 gain"
		::= { hae3000c01v1Entry 85 }

		-- 1.3.6.1.4.1.10106.3.101291.1.1.87
		hae3000c01v1Grp4P0AGain OBJECT-TYPE
			SYNTAX Gain24dbMute
			MAX-ACCESS read-write
			STATUS current
			DESCRIPTION
				"Group 4 pair 0 gain"
		::= { hae3000c01v1Entry 87 }

		-- 1.3.6.1.4.1.10106.3.101291.1.1.89
		hae3000c01v1Grp4P1AGain OBJECT-TYPE
			SYNTAX Gain24dbMute
			MAX-ACCESS read-write
			STATUS current
			DESCRIPTION
				"Group 4 pair 1 gain"
		::= { hae3000c01v1Entry 89 }

		-- 1.3.6.1.4.1.10106.3.101291.1.1.91
		hae3000c01v1Grp1P0BGain OBJECT-TYPE
			SYNTAX Gain24dbMute
			MAX-ACCESS read-write
			STATUS current
			DESCRIPTION
				"Group 1 pair 0 gain"
		::= { hae3000c01v1Entry 91 }

		-- 1.3.6.1.4.1.10106.3.101291.1.1.93
		hae3000c01v1Grp1P1BGain OBJECT-TYPE
			SYNTAX Gain24dbMute
			MAX-ACCESS read-write
			STATUS current
			DESCRIPTION
				"Group 1 pair 1 gain"
		::= { hae3000c01v1Entry 93 }

		-- 1.3.6.1.4.1.10106.3.101291.1.1.95
		hae3000c01v1Grp2P0BGain OBJECT-TYPE
			SYNTAX Gain24dbMute
			MAX-ACCESS read-write
			STATUS current
			DESCRIPTION
				"Group 2 pair 0 gain"
		::= { hae3000c01v1Entry 95 }

		-- 1.3.6.1.4.1.10106.3.101291.1.1.97
		hae3000c01v1Grp2P1BGain OBJECT-TYPE
			SYNTAX Gain24dbMute
			MAX-ACCESS read-write
			STATUS current
			DESCRIPTION
				"Group 2 pair 1 gain"
		::= { hae3000c01v1Entry 97 }

		-- 1.3.6.1.4.1.10106.3.101291.1.1.99
		hae3000c01v1Grp3P0BGain OBJECT-TYPE
			SYNTAX Gain24dbMute
			MAX-ACCESS read-write
			STATUS current
			DESCRIPTION
				"Group 3 pair 0 gain"
		::= { hae3000c01v1Entry 99 }

		-- 1.3.6.1.4.1.10106.3.101291.1.1.101
		hae3000c01v1Grp3P1BGain OBJECT-TYPE
			SYNTAX Gain24dbMute
			MAX-ACCESS read-write
			STATUS current
			DESCRIPTION
				"Group 3 pair 1 gain"
		::= { hae3000c01v1Entry 101 }

		-- 1.3.6.1.4.1.10106.3.101291.1.1.103
		hae3000c01v1Grp4P0BGain OBJECT-TYPE
			SYNTAX Gain24dbMute
			MAX-ACCESS read-write
			STATUS current
			DESCRIPTION
				"Group 4 pair 0 gain"
		::= { hae3000c01v1Entry 103 }

		-- 1.3.6.1.4.1.10106.3.101291.1.1.105
		hae3000c01v1Grp4P1BGain OBJECT-TYPE
			SYNTAX Gain24dbMute
			MAX-ACCESS read-write
			STATUS current
			DESCRIPTION
				"Group 4 pair 1 gain"
		::= { hae3000c01v1Entry 105 }

		-- 1.3.6.1.4.1.10106.3.101291.1.1.107
		hae3000c01v1Grp1P0ADelay OBJECT-TYPE
			SYNTAX Uint8
			MAX-ACCESS read-write
			STATUS current
			DESCRIPTION
				"Group 1 pair 0 delay"
		::= { hae3000c01v1Entry 107 }

		-- 1.3.6.1.4.1.10106.3.101291.1.1.109
		hae3000c01v1Grp1P1ADelay OBJECT-TYPE
			SYNTAX Uint8
			MAX-ACCESS read-write
			STATUS current
			DESCRIPTION
				"Group 1 pair 1 delay"
		::= { hae3000c01v1Entry 109 }

		-- 1.3.6.1.4.1.10106.3.101291.1.1.111
		hae3000c01v1Grp2P0ADelay OBJECT-TYPE
			SYNTAX Uint8
			MAX-ACCESS read-write
			STATUS current
			DESCRIPTION
				"Group 2 pair 0 delay"
		::= { hae3000c01v1Entry 111 }

		-- 1.3.6.1.4.1.10106.3.101291.1.1.113
		hae3000c01v1Grp2P1ADelay OBJECT-TYPE
			SYNTAX Uint8
			MAX-ACCESS read-write
			STATUS current
			DESCRIPTION
				"Group 2 pair 1 delay"
		::= { hae3000c01v1Entry 113 }

		-- 1.3.6.1.4.1.10106.3.101291.1.1.115
		hae3000c01v1Grp3P0ADelay OBJECT-TYPE
			SYNTAX Uint8
			MAX-ACCESS read-write
			STATUS current
			DESCRIPTION
				"Group 3 pair 0 delay"
		::= { hae3000c01v1Entry 115 }

		-- 1.3.6.1.4.1.10106.3.101291.1.1.117
		hae3000c01v1Grp3P1ADelay OBJECT-TYPE
			SYNTAX Uint8
			MAX-ACCESS read-write
			STATUS current
			DESCRIPTION
				"Group 3 pair 1 delay"
		::= { hae3000c01v1Entry 117 }

		-- 1.3.6.1.4.1.10106.3.101291.1.1.119
		hae3000c01v1Grp4P0ADelay OBJECT-TYPE
			SYNTAX Uint8
			MAX-ACCESS read-write
			STATUS current
			DESCRIPTION
				"Group 4 pair 0 delay"
		::= { hae3000c01v1Entry 119 }

		-- 1.3.6.1.4.1.10106.3.101291.1.1.121
		hae3000c01v1Grp4P1ADelay OBJECT-TYPE
			SYNTAX Uint8
			MAX-ACCESS read-write
			STATUS current
			DESCRIPTION
				"Group 4 pair 1 delay"
		::= { hae3000c01v1Entry 121 }

		-- 1.3.6.1.4.1.10106.3.101291.1.1.123
		hae3000c01v1Grp1P0BDelay OBJECT-TYPE
			SYNTAX Uint8
			MAX-ACCESS read-write
			STATUS current
			DESCRIPTION
				"Group 1 pair 0 delay"
		::= { hae3000c01v1Entry 123 }

		-- 1.3.6.1.4.1.10106.3.101291.1.1.125
		hae3000c01v1Grp1P1BDelay OBJECT-TYPE
			SYNTAX Uint8
			MAX-ACCESS read-write
			STATUS current
			DESCRIPTION
				"Group 1 pair 1 delay"
		::= { hae3000c01v1Entry 125 }

		-- 1.3.6.1.4.1.10106.3.101291.1.1.127
		hae3000c01v1Grp2P0BDelay OBJECT-TYPE
			SYNTAX Uint8
			MAX-ACCESS read-write
			STATUS current
			DESCRIPTION
				"Group 2 pair 0 delay"
		::= { hae3000c01v1Entry 127 }

		-- 1.3.6.1.4.1.10106.3.101291.1.1.129
		hae3000c01v1Grp2P1BDelay OBJECT-TYPE
			SYNTAX Uint8
			MAX-ACCESS read-write
			STATUS current
			DESCRIPTION
				"Group 2 pair 1 delay"
		::= { hae3000c01v1Entry 129 }

		-- 1.3.6.1.4.1.10106.3.101291.1.1.131
		hae3000c01v1Grp3P0BDelay OBJECT-TYPE
			SYNTAX Uint8
			MAX-ACCESS read-write
			STATUS current
			DESCRIPTION
				"Group 3 pair 0 delay"
		::= { hae3000c01v1Entry 131 }

		-- 1.3.6.1.4.1.10106.3.101291.1.1.133
		hae3000c01v1Grp3P1BDelay OBJECT-TYPE
			SYNTAX Uint8
			MAX-ACCESS read-write
			STATUS current
			DESCRIPTION
				"Group 3 pair 1 delay"
		::= { hae3000c01v1Entry 133 }

		-- 1.3.6.1.4.1.10106.3.101291.1.1.135
		hae3000c01v1Grp4P0BDelay OBJECT-TYPE
			SYNTAX Uint8
			MAX-ACCESS read-write
			STATUS current
			DESCRIPTION
				"Group 4 pair 0 delay"
		::= { hae3000c01v1Entry 135 }

		-- 1.3.6.1.4.1.10106.3.101291.1.1.137
		hae3000c01v1Grp4P1BDelay OBJECT-TYPE
			SYNTAX Uint8
			MAX-ACCESS read-write
			STATUS current
			DESCRIPTION
				"Group 4 pair 1 delay"
		::= { hae3000c01v1Entry 137 }

		-- 1.3.6.1.4.1.10106.3.101291.1.1.139
		hae3000c01v1NoSignalA OBJECT-TYPE
			SYNTAX BitFail
			MAX-ACCESS read-only
			STATUS current
			DESCRIPTION
				"There is no SDI signal or the format is not supported"
		::= { hae3000c01v1Entry 139 }

		-- 1.3.6.1.4.1.10106.3.101291.1.1.140
		hae3000c01v1NoSignalATrapEnable OBJECT-TYPE
			SYNTAX AlarmEnable
			MAX-ACCESS read-write
			STATUS current
			DESCRIPTION
				"There is no SDI signal or the format is not supported Trap Enable"
		::= { hae3000c01v1Entry 140 }

		-- 1.3.6.1.4.1.10106.3.101291.1.1.141
		hae3000c01v1UnlockA OBJECT-TYPE
			SYNTAX BitFail
			MAX-ACCESS read-only
			STATUS current
			DESCRIPTION
				"Indicates signal unlock fail"
		::= { hae3000c01v1Entry 141 }

		-- 1.3.6.1.4.1.10106.3.101291.1.1.142
		hae3000c01v1UnlockATrapEnable OBJECT-TYPE
			SYNTAX AlarmEnable
			MAX-ACCESS read-write
			STATUS current
			DESCRIPTION
				"Indicates signal unlock fail Trap Enable"
		::= { hae3000c01v1Entry 142 }

		-- 1.3.6.1.4.1.10106.3.101291.1.1.143
		hae3000c01v1EdhErrorA OBJECT-TYPE
			SYNTAX BitFail
			MAX-ACCESS read-only
			STATUS current
			DESCRIPTION
				"There are EDH/CRC errors on SDI signal"
		::= { hae3000c01v1Entry 143 }

		-- 1.3.6.1.4.1.10106.3.101291.1.1.144
		hae3000c01v1EdhErrorATrapEnable OBJECT-TYPE
			SYNTAX AlarmEnable
			MAX-ACCESS read-write
			STATUS current
			DESCRIPTION
				"There are EDH/CRC errors on SDI signal Trap Enable"
		::= { hae3000c01v1Entry 144 }

		-- 1.3.6.1.4.1.10106.3.101291.1.1.145
		hae3000c01v1AesFailA OBJECT-TYPE
			SYNTAX BitFail
			MAX-ACCESS read-only
			STATUS current
			DESCRIPTION
				"Sampling rate is not valid"
		::= { hae3000c01v1Entry 145 }

		-- 1.3.6.1.4.1.10106.3.101291.1.1.146
		hae3000c01v1AesFailATrapEnable OBJECT-TYPE
			SYNTAX AlarmEnable
			MAX-ACCESS read-write
			STATUS current
			DESCRIPTION
				"Sampling rate is not valid Trap Enable"
		::= { hae3000c01v1Entry 146 }

		-- 1.3.6.1.4.1.10106.3.101291.1.1.147
		hae3000c01v1DeemFailA OBJECT-TYPE
			SYNTAX BitFail
			MAX-ACCESS read-only
			STATUS current
			DESCRIPTION
				"There is no valid deembedded audio"
		::= { hae3000c01v1Entry 147 }

		-- 1.3.6.1.4.1.10106.3.101291.1.1.148
		hae3000c01v1DeemFailATrapEnable OBJECT-TYPE
			SYNTAX AlarmEnable
			MAX-ACCESS read-write
			STATUS current
			DESCRIPTION
				"There is no valid deembedded audio Trap Enable"
		::= { hae3000c01v1Entry 148 }

		-- 1.3.6.1.4.1.10106.3.101291.1.1.149
		hae3000c01v1DeemOvlA OBJECT-TYPE
			SYNTAX BitFail
			MAX-ACCESS read-only
			STATUS current
			DESCRIPTION
				"There is overload or silence in embed audio"
		::= { hae3000c01v1Entry 149 }

		-- 1.3.6.1.4.1.10106.3.101291.1.1.150
		hae3000c01v1DeemOvlATrapEnable OBJECT-TYPE
			SYNTAX AlarmEnable
			MAX-ACCESS read-write
			STATUS current
			DESCRIPTION
				"There is overload or silence in embed audio Trap Enable"
		::= { hae3000c01v1Entry 150 }

		-- 1.3.6.1.4.1.10106.3.101291.1.1.151
		hae3000c01v1ClippingA OBJECT-TYPE
			SYNTAX BitFail
			MAX-ACCESS read-only
			STATUS current
			DESCRIPTION
				"Analog input clipping"
		::= { hae3000c01v1Entry 151 }

		-- 1.3.6.1.4.1.10106.3.101291.1.1.152
		hae3000c01v1ClippingATrapEnable OBJECT-TYPE
			SYNTAX AlarmEnable
			MAX-ACCESS read-write
			STATUS current
			DESCRIPTION
				"Analog input clipping Trap Enable"
		::= { hae3000c01v1Entry 152 }

		-- 1.3.6.1.4.1.10106.3.101291.1.1.153
		hae3000c01v1FormatA OBJECT-TYPE
			SYNTAX SdiHd3gFmt3
			MAX-ACCESS read-only
			STATUS current
			DESCRIPTION
				"Indicates the SDI transmited signal format"
		::= { hae3000c01v1Entry 153 }

		-- 1.3.6.1.4.1.10106.3.101291.1.1.155
		hae3000c01v1NoSignalB OBJECT-TYPE
			SYNTAX BitFail
			MAX-ACCESS read-only
			STATUS current
			DESCRIPTION
				"There is no SDI signal or the format is not supported"
		::= { hae3000c01v1Entry 155 }

		-- 1.3.6.1.4.1.10106.3.101291.1.1.156
		hae3000c01v1NoSignalBTrapEnable OBJECT-TYPE
			SYNTAX AlarmEnable
			MAX-ACCESS read-write
			STATUS current
			DESCRIPTION
				"There is no SDI signal or the format is not supported Trap Enable"
		::= { hae3000c01v1Entry 156 }

		-- 1.3.6.1.4.1.10106.3.101291.1.1.157
		hae3000c01v1UnlockB OBJECT-TYPE
			SYNTAX BitFail
			MAX-ACCESS read-only
			STATUS current
			DESCRIPTION
				"Indicates signal unlock fail"
		::= { hae3000c01v1Entry 157 }

		-- 1.3.6.1.4.1.10106.3.101291.1.1.158
		hae3000c01v1UnlockBTrapEnable OBJECT-TYPE
			SYNTAX AlarmEnable
			MAX-ACCESS read-write
			STATUS current
			DESCRIPTION
				"Indicates signal unlock fail Trap Enable"
		::= { hae3000c01v1Entry 158 }

		-- 1.3.6.1.4.1.10106.3.101291.1.1.159
		hae3000c01v1EdhErrorB OBJECT-TYPE
			SYNTAX BitFail
			MAX-ACCESS read-only
			STATUS current
			DESCRIPTION
				"There are EDH/CRC errors on SDI signal"
		::= { hae3000c01v1Entry 159 }

		-- 1.3.6.1.4.1.10106.3.101291.1.1.160
		hae3000c01v1EdhErrorBTrapEnable OBJECT-TYPE
			SYNTAX AlarmEnable
			MAX-ACCESS read-write
			STATUS current
			DESCRIPTION
				"There are EDH/CRC errors on SDI signal Trap Enable"
		::= { hae3000c01v1Entry 160 }

		-- 1.3.6.1.4.1.10106.3.101291.1.1.161
		hae3000c01v1AesFailB OBJECT-TYPE
			SYNTAX BitFail
			MAX-ACCESS read-only
			STATUS current
			DESCRIPTION
				"Sampling rate is not valid"
		::= { hae3000c01v1Entry 161 }

		-- 1.3.6.1.4.1.10106.3.101291.1.1.162
		hae3000c01v1AesFailBTrapEnable OBJECT-TYPE
			SYNTAX AlarmEnable
			MAX-ACCESS read-write
			STATUS current
			DESCRIPTION
				"Sampling rate is not valid Trap Enable"
		::= { hae3000c01v1Entry 162 }

		-- 1.3.6.1.4.1.10106.3.101291.1.1.163
		hae3000c01v1DeemFailB OBJECT-TYPE
			SYNTAX BitFail
			MAX-ACCESS read-only
			STATUS current
			DESCRIPTION
				"There is no valid deembedded audio"
		::= { hae3000c01v1Entry 163 }

		-- 1.3.6.1.4.1.10106.3.101291.1.1.164
		hae3000c01v1DeemFailBTrapEnable OBJECT-TYPE
			SYNTAX AlarmEnable
			MAX-ACCESS read-write
			STATUS current
			DESCRIPTION
				"There is no valid deembedded audio Trap Enable"
		::= { hae3000c01v1Entry 164 }

		-- 1.3.6.1.4.1.10106.3.101291.1.1.165
		hae3000c01v1DeemOvlB OBJECT-TYPE
			SYNTAX BitFail
			MAX-ACCESS read-only
			STATUS current
			DESCRIPTION
				"There is overload or silence in embed audio"
		::= { hae3000c01v1Entry 165 }

		-- 1.3.6.1.4.1.10106.3.101291.1.1.166
		hae3000c01v1DeemOvlBTrapEnable OBJECT-TYPE
			SYNTAX AlarmEnable
			MAX-ACCESS read-write
			STATUS current
			DESCRIPTION
				"There is overload or silence in embed audio Trap Enable"
		::= { hae3000c01v1Entry 166 }

		-- 1.3.6.1.4.1.10106.3.101291.1.1.167
		hae3000c01v1ClippingB OBJECT-TYPE
			SYNTAX BitFail
			MAX-ACCESS read-only
			STATUS current
			DESCRIPTION
				"Analog input clipping"
		::= { hae3000c01v1Entry 167 }

		-- 1.3.6.1.4.1.10106.3.101291.1.1.168
		hae3000c01v1ClippingBTrapEnable OBJECT-TYPE
			SYNTAX AlarmEnable
			MAX-ACCESS read-write
			STATUS current
			DESCRIPTION
				"Analog input clipping Trap Enable"
		::= { hae3000c01v1Entry 168 }

		-- 1.3.6.1.4.1.10106.3.101291.1.1.169
		hae3000c01v1FormatB OBJECT-TYPE
			SYNTAX SdiHd3gFmt3
			MAX-ACCESS read-only
			STATUS current
			DESCRIPTION
				"Indicates the SDI transmited signal format"
		::= { hae3000c01v1Entry 169 }

		-- 1.3.6.1.4.1.10106.3.101291.1.1.171
		hae3000c01v1SerialNo OBJECT-TYPE
			SYNTAX SerialNo
			MAX-ACCESS read-only
			STATUS current
			DESCRIPTION
				"Serial number"
		::= { hae3000c01v1Entry 171 }

		-- 1.3.6.1.4.1.10106.3.101291.1.1.215
		hae3000c01v1CorteSelChB OBJECT-TYPE
			SYNTAX Bit0BlBit1Cut
			MAX-ACCESS read-write
			STATUS current
			DESCRIPTION
				"Selects the action to perform when the input signal is absent"
		::= { hae3000c01v1Entry 215 }

		-- 1.3.6.1.4.1.10106.3.360001
		had3000c01v1 OBJECT IDENTIFIER ::= { albalaProducts 360001 }

		-- 1.3.6.1.4.1.10106.3.360001.1
		had3000c01v1Table  OBJECT-TYPE
			SYNTAX SEQUENCE OF Had3000c01v1Entry
			MAX-ACCESS not-accessible
			STATUS current
			DESCRIPTION
				"Module  HAD3000C01V1 Table"
			::= { had3000c01v1 1 }

		-- 1.3.6.1.4.1.10106.3.360001.1.1
		had3000c01v1Entry  OBJECT-TYPE
			SYNTAX Had3000c01v1Entry
			MAX-ACCESS not-accessible
			STATUS current
			DESCRIPTION
				"Module HAD3000C01V1 Entry"
			INDEX { had3000c01v1Index }
			::= { had3000c01v1Table 1 }

			Had3000c01v1Entry ::=
			SEQUENCE {
				had3000c01v1Index
				ModuleIndex,
				had3000c01v1RestorPreset
				PresetRestore,
				had3000c01v1ActivePreset
				PresetActive,
				had3000c01v1LoadPreset
				PresetLoad,
				had3000c01v1SavePreset
				PresetSave,
				had3000c01v1ClnGr1A
				Bit0No1Yes,
				had3000c01v1ClnGr2A
				Bit0No1Yes,
				had3000c01v1ClnGr3A
				Bit0No1Yes,
				had3000c01v1ClnGr4A
				Bit0No1Yes,
				had3000c01v1ClnGr1B
				Bit0No1Yes,
				had3000c01v1ClnGr2B
				Bit0No1Yes,
				had3000c01v1ClnGr3B
				Bit0No1Yes,
				had3000c01v1ClnGr4B
				Bit0No1Yes,
				had3000c01v1Grp1P0A
				AudioMxInput4,
				had3000c01v1Grp1P1A
				AudioMxInput4,
				had3000c01v1Grp2P0A
				AudioMxInput4,
				had3000c01v1Grp2P1A
				AudioMxInput4,
				had3000c01v1Grp3P0A
				AudioMxInput4,
				had3000c01v1Grp3P1A
				AudioMxInput4,
				had3000c01v1Grp4P0A
				AudioMxInput4,
				had3000c01v1Grp4P1A
				AudioMxInput4,
				had3000c01v1Grp1P0B
				AudioMxInput4,
				had3000c01v1Grp1P1B
				AudioMxInput4,
				had3000c01v1Grp2P0B
				AudioMxInput4,
				had3000c01v1Grp2P1B
				AudioMxInput4,
				had3000c01v1Grp3P0B
				AudioMxInput4,
				had3000c01v1Grp3P1B
				AudioMxInput4,
				had3000c01v1Grp4P0B
				AudioMxInput4,
				had3000c01v1Grp4P1B
				AudioMxInput4,
				had3000c01v1Aes1A
				AudioMxInput4,
				had3000c01v1Aes2A
				AudioMxInput4,
				had3000c01v1Aes1B
				AudioMxInput4,
				had3000c01v1Aes2B
				AudioMxInput4,
				had3000c01v1FullScaleLev
				Uint5,
				had3000c01v1SamplingClkA
				HaeSampClk,
				had3000c01v1SamplingClkB
				HaeSampClk,
				had3000c01v1OvldLevel
				LevelDbfs4,
				had3000c01v1SilenceLevel
				LevelDbfs3,
				had3000c01v1SilenceTime
				TimeS2,
				had3000c01v1DelayMode
				Bit0Out1In,
				had3000c01v1DelaySteps
				TimeX1Ms,
				had3000c01v1Grp1P0AGain
				Gain24dbMute,
				had3000c01v1Grp1P1AGain
				Gain24dbMute,
				had3000c01v1Grp2P0AGain
				Gain24dbMute,
				had3000c01v1Grp2P1AGain
				Gain24dbMute,
				had3000c01v1Grp3P0AGain
				Gain24dbMute,
				had3000c01v1Grp3P1AGain
				Gain24dbMute,
				had3000c01v1Grp4P0AGain
				Gain24dbMute,
				had3000c01v1Grp4P1AGain
				Gain24dbMute,
				had3000c01v1Grp1P0BGain
				Gain24dbMute,
				had3000c01v1Grp1P1BGain
				Gain24dbMute,
				had3000c01v1Grp2P0BGain
				Gain24dbMute,
				had3000c01v1Grp2P1BGain
				Gain24dbMute,
				had3000c01v1Grp3P0BGain
				Gain24dbMute,
				had3000c01v1Grp3P1BGain
				Gain24dbMute,
				had3000c01v1Grp4P0BGain
				Gain24dbMute,
				had3000c01v1Grp4P1BGain
				Gain24dbMute,
				had3000c01v1Aes1AGain
				Gain24dbMute,
				had3000c01v1Aes2AGain
				Gain24dbMute,
				had3000c01v1Aes1BGain
				Gain24dbMute,
				had3000c01v1Aes2BGain
				Gain24dbMute,
				had3000c01v1Grp1P0ADelay
				Uint8,
				had3000c01v1Grp1P1ADelay
				Uint8,
				had3000c01v1Grp2P0ADelay
				Uint8,
				had3000c01v1Grp2P1ADelay
				Uint8,
				had3000c01v1Grp3P0ADelay
				Uint8,
				had3000c01v1Grp3P1ADelay
				Uint8,
				had3000c01v1Grp4P0ADelay
				Uint8,
				had3000c01v1Grp4P1ADelay
				Uint8,
				had3000c01v1Grp1P0BDelay
				Uint8,
				had3000c01v1Grp1P1BDelay
				Uint8,
				had3000c01v1Grp2P0BDelay
				Uint8,
				had3000c01v1Grp2P1BDelay
				Uint8,
				had3000c01v1Grp3P0BDelay
				Uint8,
				had3000c01v1Grp3P1BDelay
				Uint8,
				had3000c01v1Grp4P0BDelay
				Uint8,
				had3000c01v1Grp4P1BDelay
				Uint8,
				had3000c01v1Aes1ADelay
				Uint8,
				had3000c01v1Aes2ADelay
				Uint8,
				had3000c01v1Aes1BDelay
				Uint8,
				had3000c01v1Aes2BDelay
				Uint8,
				had3000c01v1NoSignalA
				BitFail,
				had3000c01v1NoSignalATrapEnable
				AlarmEnable,
				had3000c01v1UnlockA
				BitFail,
				had3000c01v1UnlockATrapEnable
				AlarmEnable,
				had3000c01v1EdhErrorA
				BitFail,
				had3000c01v1EdhErrorATrapEnable
				AlarmEnable,
				had3000c01v1SampRFailA
				BitFail,
				had3000c01v1SampRFailATrapEnable
				AlarmEnable,
				had3000c01v1DeemFailA
				BitFail,
				had3000c01v1DeemFailATrapEnable
				AlarmEnable,
				had3000c01v1AesOvlA
				BitFail,
				had3000c01v1AesOvlATrapEnable
				AlarmEnable,
				had3000c01v1DeemOvlA
				BitFail,
				had3000c01v1DeemOvlATrapEnable
				AlarmEnable,
				had3000c01v1FormatA
				SdiHd3gFmt3,
				had3000c01v1NoSignalB
				BitFail,
				had3000c01v1NoSignalBTrapEnable
				AlarmEnable,
				had3000c01v1UnlockB
				BitFail,
				had3000c01v1UnlockBTrapEnable
				AlarmEnable,
				had3000c01v1EdhErrorB
				BitFail,
				had3000c01v1EdhErrorBTrapEnable
				AlarmEnable,
				had3000c01v1SampRFailB
				BitFail,
				had3000c01v1SampRFailBTrapEnable
				AlarmEnable,
				had3000c01v1DeemFailB
				BitFail,
				had3000c01v1DeemFailBTrapEnable
				AlarmEnable,
				had3000c01v1AesOvlB
				BitFail,
				had3000c01v1AesOvlBTrapEnable
				AlarmEnable,
				had3000c01v1DeemOvlB
				BitFail,
				had3000c01v1DeemOvlBTrapEnable
				AlarmEnable,
				had3000c01v1FormatB
				SdiHd3gFmt3,
				had3000c01v1SerialNo
				SerialNo,
				had3000c01v1CorteSelChB
				Bit0BlBit1Cut
			 }

		-- 1.3.6.1.4.1.10106.3.101291.1.1.1
		had3000c01v1Index OBJECT-TYPE
			SYNTAX ModuleIndex
			MAX-ACCESS read-only
			STATUS current
			DESCRIPTION
				"Index of HAD3000C01V1 Table"
		::= { had3000c01v1Entry 1 }

		-- 1.3.6.1.4.1.10106.3.101291.1.1.3
		had3000c01v1RestorPreset OBJECT-TYPE
			SYNTAX PresetRestore
			MAX-ACCESS read-write
			STATUS current
			DESCRIPTION
				"Allows restoring a factory preset"
		::= { had3000c01v1Entry 3 }

		-- 1.3.6.1.4.1.10106.3.101291.1.1.5
		had3000c01v1ActivePreset OBJECT-TYPE
			SYNTAX PresetActive
			MAX-ACCESS read-only
			STATUS current
			DESCRIPTION
				"Shows the active preset"
		::= { had3000c01v1Entry 5 }

		-- 1.3.6.1.4.1.10106.3.101291.1.1.7
		had3000c01v1LoadPreset OBJECT-TYPE
			SYNTAX PresetLoad
			MAX-ACCESS read-write
			STATUS current
			DESCRIPTION
				"Allows loading a preset"
		::= { had3000c01v1Entry 7 }

		-- 1.3.6.1.4.1.10106.3.101291.1.1.9
		had3000c01v1SavePreset OBJECT-TYPE
			SYNTAX PresetSave
			MAX-ACCESS read-write
			STATUS current
			DESCRIPTION
				"Allows saving a preset"
		::= { had3000c01v1Entry 9 }

		-- 1.3.6.1.4.1.10106.3.101291.1.1.11
		had3000c01v1ClnGr1A OBJECT-TYPE
			SYNTAX Bit0No1Yes
			MAX-ACCESS read-write
			STATUS current
			DESCRIPTION
				"Allows selecting if all the group 1 audio packets are deleted after deembedding"
		::= { had3000c01v1Entry 11 }

		-- 1.3.6.1.4.1.10106.3.101291.1.1.13
		had3000c01v1ClnGr2A OBJECT-TYPE
			SYNTAX Bit0No1Yes
			MAX-ACCESS read-write
			STATUS current
			DESCRIPTION
				"Allows selecting if all the group 2 audio packets are deleted after deembedding"
		::= { had3000c01v1Entry 13 }

		-- 1.3.6.1.4.1.10106.3.101291.1.1.15
		had3000c01v1ClnGr3A OBJECT-TYPE
			SYNTAX Bit0No1Yes
			MAX-ACCESS read-write
			STATUS current
			DESCRIPTION
				"Allows selecting if all the group 3 audio packets are deleted after deembedding"
		::= { had3000c01v1Entry 15 }

		-- 1.3.6.1.4.1.10106.3.101291.1.1.17
		had3000c01v1ClnGr4A OBJECT-TYPE
			SYNTAX Bit0No1Yes
			MAX-ACCESS read-write
			STATUS current
			DESCRIPTION
				"Allows selecting if all the group 4 audio packets are deleted after deembedding"
		::= { had3000c01v1Entry 17 }

		-- 1.3.6.1.4.1.10106.3.101291.1.1.19
		had3000c01v1ClnGr1B OBJECT-TYPE
			SYNTAX Bit0No1Yes
			MAX-ACCESS read-write
			STATUS current
			DESCRIPTION
				"Allows selecting if all the group 1 audio packets are deleted after deembedding"
		::= { had3000c01v1Entry 19 }

		-- 1.3.6.1.4.1.10106.3.101291.1.1.21
		had3000c01v1ClnGr2B OBJECT-TYPE
			SYNTAX Bit0No1Yes
			MAX-ACCESS read-write
			STATUS current
			DESCRIPTION
				"Allows selecting if all the group 2 audio packets are deleted after deembedding"
		::= { had3000c01v1Entry 21 }

		-- 1.3.6.1.4.1.10106.3.101291.1.1.23
		had3000c01v1ClnGr3B OBJECT-TYPE
			SYNTAX Bit0No1Yes
			MAX-ACCESS read-write
			STATUS current
			DESCRIPTION
				"Allows selecting if all the group 3 audio packets are deleted after deembedding"
		::= { had3000c01v1Entry 23 }

		-- 1.3.6.1.4.1.10106.3.101291.1.1.25
		had3000c01v1ClnGr4B OBJECT-TYPE
			SYNTAX Bit0No1Yes
			MAX-ACCESS read-write
			STATUS current
			DESCRIPTION
				"Allows selecting if all the group 4 audio packets are deleted after deembedding"
		::= { had3000c01v1Entry 25 }

		-- 1.3.6.1.4.1.10106.3.101291.1.1.27
		had3000c01v1Grp1P0A OBJECT-TYPE
			SYNTAX AudioMxInput4
			MAX-ACCESS read-write
			STATUS current
			DESCRIPTION
				"Allows selecting the audio embedded in group 1 pair 0"
		::= { had3000c01v1Entry 27 }

		-- 1.3.6.1.4.1.10106.3.101291.1.1.29
		had3000c01v1Grp1P1A OBJECT-TYPE
			SYNTAX AudioMxInput4
			MAX-ACCESS read-write
			STATUS current
			DESCRIPTION
				"Allows selecting the audio embedded in group 1 pair 1"
		::= { had3000c01v1Entry 29 }

		-- 1.3.6.1.4.1.10106.3.101291.1.1.31
		had3000c01v1Grp2P0A OBJECT-TYPE
			SYNTAX AudioMxInput4
			MAX-ACCESS read-write
			STATUS current
			DESCRIPTION
				"Allows selecting the audio embedded in group 2 pair 0"
		::= { had3000c01v1Entry 31 }

		-- 1.3.6.1.4.1.10106.3.101291.1.1.33
		had3000c01v1Grp2P1A OBJECT-TYPE
			SYNTAX AudioMxInput4
			MAX-ACCESS read-write
			STATUS current
			DESCRIPTION
				"Allows selecting the audio embedded in group 2 pair 1"
		::= { had3000c01v1Entry 33 }

		-- 1.3.6.1.4.1.10106.3.101291.1.1.35
		had3000c01v1Grp3P0A OBJECT-TYPE
			SYNTAX AudioMxInput4
			MAX-ACCESS read-write
			STATUS current
			DESCRIPTION
				"Allows selecting the audio embedded in group 3 pair 0"
		::= { had3000c01v1Entry 35 }

		-- 1.3.6.1.4.1.10106.3.101291.1.1.37
		had3000c01v1Grp3P1A OBJECT-TYPE
			SYNTAX AudioMxInput4
			MAX-ACCESS read-write
			STATUS current
			DESCRIPTION
				"Allows selecting the audio embedded in group 3 pair 1"
		::= { had3000c01v1Entry 37 }

		-- 1.3.6.1.4.1.10106.3.101291.1.1.39
		had3000c01v1Grp4P0A OBJECT-TYPE
			SYNTAX AudioMxInput4
			MAX-ACCESS read-write
			STATUS current
			DESCRIPTION
				"Allows selecting the audio embedded in group 4 pair 0"
		::= { had3000c01v1Entry 39 }

		-- 1.3.6.1.4.1.10106.3.101291.1.1.41
		had3000c01v1Grp4P1A OBJECT-TYPE
			SYNTAX AudioMxInput4
			MAX-ACCESS read-write
			STATUS current
			DESCRIPTION
				"Allows selecting the audio embedded in group 4 pair 1"
		::= { had3000c01v1Entry 41 }

		-- 1.3.6.1.4.1.10106.3.101291.1.1.43
		had3000c01v1Grp1P0B OBJECT-TYPE
			SYNTAX AudioMxInput4
			MAX-ACCESS read-write
			STATUS current
			DESCRIPTION
				"Allows selecting the audio embedded in group 1 pair 0"
		::= { had3000c01v1Entry 43 }

		-- 1.3.6.1.4.1.10106.3.101291.1.1.45
		had3000c01v1Grp1P1B OBJECT-TYPE
			SYNTAX AudioMxInput4
			MAX-ACCESS read-write
			STATUS current
			DESCRIPTION
				"Allows selecting the audio embedded in group 1 pair 1"
		::= { had3000c01v1Entry 45 }

		-- 1.3.6.1.4.1.10106.3.101291.1.1.47
		had3000c01v1Grp2P0B OBJECT-TYPE
			SYNTAX AudioMxInput4
			MAX-ACCESS read-write
			STATUS current
			DESCRIPTION
				"Allows selecting the audio embedded in group 2 pair 0"
		::= { had3000c01v1Entry 47 }

		-- 1.3.6.1.4.1.10106.3.101291.1.1.49
		had3000c01v1Grp2P1B OBJECT-TYPE
			SYNTAX AudioMxInput4
			MAX-ACCESS read-write
			STATUS current
			DESCRIPTION
				"Allows selecting the audio embedded in group 2 pair 1"
		::= { had3000c01v1Entry 49 }

		-- 1.3.6.1.4.1.10106.3.101291.1.1.51
		had3000c01v1Grp3P0B OBJECT-TYPE
			SYNTAX AudioMxInput4
			MAX-ACCESS read-write
			STATUS current
			DESCRIPTION
				"Allows selecting the audio embedded in group 3 pair 0"
		::= { had3000c01v1Entry 51 }

		-- 1.3.6.1.4.1.10106.3.101291.1.1.53
		had3000c01v1Grp3P1B OBJECT-TYPE
			SYNTAX AudioMxInput4
			MAX-ACCESS read-write
			STATUS current
			DESCRIPTION
				"Allows selecting the audio embedded in group 3 pair 1"
		::= { had3000c01v1Entry 53 }

		-- 1.3.6.1.4.1.10106.3.101291.1.1.55
		had3000c01v1Grp4P0B OBJECT-TYPE
			SYNTAX AudioMxInput4
			MAX-ACCESS read-write
			STATUS current
			DESCRIPTION
				"Allows selecting the audio embedded in group 4 pair 0"
		::= { had3000c01v1Entry 55 }

		-- 1.3.6.1.4.1.10106.3.101291.1.1.57
		had3000c01v1Grp4P1B OBJECT-TYPE
			SYNTAX AudioMxInput4
			MAX-ACCESS read-write
			STATUS current
			DESCRIPTION
				"Allows selecting the audio embedded in group 4 pair 1"
		::= { had3000c01v1Entry 57 }

		-- 1.3.6.1.4.1.10106.3.101291.1.1.59
		had3000c01v1Aes1A OBJECT-TYPE
			SYNTAX AudioMxInput4
			MAX-ACCESS read-write
			STATUS current
			DESCRIPTION
				"Allows selecting the audio deembedded in STRM1"
		::= { had3000c01v1Entry 59 }

		-- 1.3.6.1.4.1.10106.3.101291.1.1.61
		had3000c01v1Aes2A OBJECT-TYPE
			SYNTAX AudioMxInput4
			MAX-ACCESS read-write
			STATUS current
			DESCRIPTION
				"Allows selecting the audio deembedded in STRM2"
		::= { had3000c01v1Entry 61 }

		-- 1.3.6.1.4.1.10106.3.101291.1.1.63
		had3000c01v1Aes1B OBJECT-TYPE
			SYNTAX AudioMxInput4
			MAX-ACCESS read-write
			STATUS current
			DESCRIPTION
				"Allows selecting the audio deembedded in STRM1"
		::= { had3000c01v1Entry 63 }

		-- 1.3.6.1.4.1.10106.3.101291.1.1.65
		had3000c01v1Aes2B OBJECT-TYPE
			SYNTAX AudioMxInput4
			MAX-ACCESS read-write
			STATUS current
			DESCRIPTION
				"Allows selecting the audio deembedded in STMR2"
		::= { had3000c01v1Entry 65 }

		-- 1.3.6.1.4.1.10106.3.101291.1.1.67
		had3000c01v1FullScaleLev OBJECT-TYPE
			SYNTAX Uint5
			MAX-ACCESS read-write
			STATUS current
			DESCRIPTION
				"Full scale level"
		::= { had3000c01v1Entry 67 }

		-- 1.3.6.1.4.1.10106.3.101291.1.1.69
		had3000c01v1SamplingClkA OBJECT-TYPE
			SYNTAX HaeSampClk
			MAX-ACCESS read-write
			STATUS current
			DESCRIPTION
				"Sampling clock"
		::= { had3000c01v1Entry 69 }

		-- 1.3.6.1.4.1.10106.3.101291.1.1.71
		had3000c01v1SamplingClkB OBJECT-TYPE
			SYNTAX HaeSampClk
			MAX-ACCESS read-write
			STATUS current
			DESCRIPTION
				"Sampling clock"
		::= { had3000c01v1Entry 71 }

		-- 1.3.6.1.4.1.10106.3.101291.1.1.73
		had3000c01v1OvldLevel OBJECT-TYPE
			SYNTAX LevelDbfs4
			MAX-ACCESS read-write
			STATUS current
			DESCRIPTION
				"Allows adjusting the threshold level for the overload detector"
		::= { had3000c01v1Entry 73 }

		-- 1.3.6.1.4.1.10106.3.101291.1.1.75
		had3000c01v1SilenceLevel OBJECT-TYPE
			SYNTAX LevelDbfs3
			MAX-ACCESS read-write
			STATUS current
			DESCRIPTION
				"Allows adjusting the threshold level for the silence detector"
		::= { had3000c01v1Entry 75 }

		-- 1.3.6.1.4.1.10106.3.101291.1.1.77
		had3000c01v1SilenceTime OBJECT-TYPE
			SYNTAX TimeS2
			MAX-ACCESS read-write
			STATUS current
			DESCRIPTION
				"Allows adjusting the silence time"
		::= { had3000c01v1Entry 77 }

		-- 1.3.6.1.4.1.10106.3.101291.1.1.79
		had3000c01v1DelayMode OBJECT-TYPE
			SYNTAX Bit0Out1In
			MAX-ACCESS read-write
			STATUS current
			DESCRIPTION
				"Allows selecting the delay module location"
		::= { had3000c01v1Entry 79 }

		-- 1.3.6.1.4.1.10106.3.101291.1.1.81
		had3000c01v1DelaySteps OBJECT-TYPE
			SYNTAX TimeX1Ms
			MAX-ACCESS read-write
			STATUS current
			DESCRIPTION
				"Allows adjusting the delay step for all delay controls"
		::= { had3000c01v1Entry 81 }

		-- 1.3.6.1.4.1.10106.3.101291.1.1.83
		had3000c01v1Grp1P0AGain OBJECT-TYPE
			SYNTAX Gain24dbMute
			MAX-ACCESS read-write
			STATUS current
			DESCRIPTION
				"Group 1 pair 0 gain"
		::= { had3000c01v1Entry 83 }

		-- 1.3.6.1.4.1.10106.3.101291.1.1.85
		had3000c01v1Grp1P1AGain OBJECT-TYPE
			SYNTAX Gain24dbMute
			MAX-ACCESS read-write
			STATUS current
			DESCRIPTION
				"Group 1 pair 1 gain"
		::= { had3000c01v1Entry 85 }

		-- 1.3.6.1.4.1.10106.3.101291.1.1.87
		had3000c01v1Grp2P0AGain OBJECT-TYPE
			SYNTAX Gain24dbMute
			MAX-ACCESS read-write
			STATUS current
			DESCRIPTION
				"Group 2 pair 0 gain"
		::= { had3000c01v1Entry 87 }

		-- 1.3.6.1.4.1.10106.3.101291.1.1.89
		had3000c01v1Grp2P1AGain OBJECT-TYPE
			SYNTAX Gain24dbMute
			MAX-ACCESS read-write
			STATUS current
			DESCRIPTION
				"Group 2 pair 1 gain"
		::= { had3000c01v1Entry 89 }

		-- 1.3.6.1.4.1.10106.3.101291.1.1.91
		had3000c01v1Grp3P0AGain OBJECT-TYPE
			SYNTAX Gain24dbMute
			MAX-ACCESS read-write
			STATUS current
			DESCRIPTION
				"Group 3 pair 0 gain"
		::= { had3000c01v1Entry 91 }

		-- 1.3.6.1.4.1.10106.3.101291.1.1.93
		had3000c01v1Grp3P1AGain OBJECT-TYPE
			SYNTAX Gain24dbMute
			MAX-ACCESS read-write
			STATUS current
			DESCRIPTION
				"Group 3 pair 1 gain"
		::= { had3000c01v1Entry 93 }

		-- 1.3.6.1.4.1.10106.3.101291.1.1.95
		had3000c01v1Grp4P0AGain OBJECT-TYPE
			SYNTAX Gain24dbMute
			MAX-ACCESS read-write
			STATUS current
			DESCRIPTION
				"Group 4 pair 0 gain"
		::= { had3000c01v1Entry 95 }

		-- 1.3.6.1.4.1.10106.3.101291.1.1.97
		had3000c01v1Grp4P1AGain OBJECT-TYPE
			SYNTAX Gain24dbMute
			MAX-ACCESS read-write
			STATUS current
			DESCRIPTION
				"Group 4 pair 1 gain"
		::= { had3000c01v1Entry 97 }

		-- 1.3.6.1.4.1.10106.3.101291.1.1.99
		had3000c01v1Grp1P0BGain OBJECT-TYPE
			SYNTAX Gain24dbMute
			MAX-ACCESS read-write
			STATUS current
			DESCRIPTION
				"Group 1 pair 0 gain"
		::= { had3000c01v1Entry 99 }

		-- 1.3.6.1.4.1.10106.3.101291.1.1.101
		had3000c01v1Grp1P1BGain OBJECT-TYPE
			SYNTAX Gain24dbMute
			MAX-ACCESS read-write
			STATUS current
			DESCRIPTION
				"Group 1 pair 1 gain"
		::= { had3000c01v1Entry 101 }

		-- 1.3.6.1.4.1.10106.3.101291.1.1.103
		had3000c01v1Grp2P0BGain OBJECT-TYPE
			SYNTAX Gain24dbMute
			MAX-ACCESS read-write
			STATUS current
			DESCRIPTION
				"Group 2 pair 0 gain"
		::= { had3000c01v1Entry 103 }

		-- 1.3.6.1.4.1.10106.3.101291.1.1.105
		had3000c01v1Grp2P1BGain OBJECT-TYPE
			SYNTAX Gain24dbMute
			MAX-ACCESS read-write
			STATUS current
			DESCRIPTION
				"Group 2 pair 1 gain"
		::= { had3000c01v1Entry 105 }

		-- 1.3.6.1.4.1.10106.3.101291.1.1.107
		had3000c01v1Grp3P0BGain OBJECT-TYPE
			SYNTAX Gain24dbMute
			MAX-ACCESS read-write
			STATUS current
			DESCRIPTION
				"Group 3 pair 0 gain"
		::= { had3000c01v1Entry 107 }

		-- 1.3.6.1.4.1.10106.3.101291.1.1.109
		had3000c01v1Grp3P1BGain OBJECT-TYPE
			SYNTAX Gain24dbMute
			MAX-ACCESS read-write
			STATUS current
			DESCRIPTION
				"Group 3 pair 1 gain"
		::= { had3000c01v1Entry 109 }

		-- 1.3.6.1.4.1.10106.3.101291.1.1.111
		had3000c01v1Grp4P0BGain OBJECT-TYPE
			SYNTAX Gain24dbMute
			MAX-ACCESS read-write
			STATUS current
			DESCRIPTION
				"Group 4 pair 0 gain"
		::= { had3000c01v1Entry 111 }

		-- 1.3.6.1.4.1.10106.3.101291.1.1.113
		had3000c01v1Grp4P1BGain OBJECT-TYPE
			SYNTAX Gain24dbMute
			MAX-ACCESS read-write
			STATUS current
			DESCRIPTION
				"Group 4 pair 1 gain"
		::= { had3000c01v1Entry 113 }

		-- 1.3.6.1.4.1.10106.3.101291.1.1.115
		had3000c01v1Aes1AGain OBJECT-TYPE
			SYNTAX Gain24dbMute
			MAX-ACCESS read-write
			STATUS current
			DESCRIPTION
				"STRM1 output gain"
		::= { had3000c01v1Entry 115 }

		-- 1.3.6.1.4.1.10106.3.101291.1.1.117
		had3000c01v1Aes2AGain OBJECT-TYPE
			SYNTAX Gain24dbMute
			MAX-ACCESS read-write
			STATUS current
			DESCRIPTION
				"STRM2 output  gain"
		::= { had3000c01v1Entry 117 }

		-- 1.3.6.1.4.1.10106.3.101291.1.1.119
		had3000c01v1Aes1BGain OBJECT-TYPE
			SYNTAX Gain24dbMute
			MAX-ACCESS read-write
			STATUS current
			DESCRIPTION
				"STRM1 output  gain"
		::= { had3000c01v1Entry 119 }

		-- 1.3.6.1.4.1.10106.3.101291.1.1.121
		had3000c01v1Aes2BGain OBJECT-TYPE
			SYNTAX Gain24dbMute
			MAX-ACCESS read-write
			STATUS current
			DESCRIPTION
				"STRM2  output gain"
		::= { had3000c01v1Entry 121 }

		-- 1.3.6.1.4.1.10106.3.101291.1.1.123
		had3000c01v1Grp1P0ADelay OBJECT-TYPE
			SYNTAX Uint8
			MAX-ACCESS read-write
			STATUS current
			DESCRIPTION
				"Group 1 pair 0 delay"
		::= { had3000c01v1Entry 123 }

		-- 1.3.6.1.4.1.10106.3.101291.1.1.125
		had3000c01v1Grp1P1ADelay OBJECT-TYPE
			SYNTAX Uint8
			MAX-ACCESS read-write
			STATUS current
			DESCRIPTION
				"Group 1 pair 1 delay"
		::= { had3000c01v1Entry 125 }

		-- 1.3.6.1.4.1.10106.3.101291.1.1.127
		had3000c01v1Grp2P0ADelay OBJECT-TYPE
			SYNTAX Uint8
			MAX-ACCESS read-write
			STATUS current
			DESCRIPTION
				"Group 2 pair 0 delay"
		::= { had3000c01v1Entry 127 }

		-- 1.3.6.1.4.1.10106.3.101291.1.1.129
		had3000c01v1Grp2P1ADelay OBJECT-TYPE
			SYNTAX Uint8
			MAX-ACCESS read-write
			STATUS current
			DESCRIPTION
				"Group 2 pair 1 delay"
		::= { had3000c01v1Entry 129 }

		-- 1.3.6.1.4.1.10106.3.101291.1.1.131
		had3000c01v1Grp3P0ADelay OBJECT-TYPE
			SYNTAX Uint8
			MAX-ACCESS read-write
			STATUS current
			DESCRIPTION
				"Group 3 pair 0 delay"
		::= { had3000c01v1Entry 131 }

		-- 1.3.6.1.4.1.10106.3.101291.1.1.133
		had3000c01v1Grp3P1ADelay OBJECT-TYPE
			SYNTAX Uint8
			MAX-ACCESS read-write
			STATUS current
			DESCRIPTION
				"Group 3 pair 1 delay"
		::= { had3000c01v1Entry 133 }

		-- 1.3.6.1.4.1.10106.3.101291.1.1.135
		had3000c01v1Grp4P0ADelay OBJECT-TYPE
			SYNTAX Uint8
			MAX-ACCESS read-write
			STATUS current
			DESCRIPTION
				"Group 4 pair 0 delay"
		::= { had3000c01v1Entry 135 }

		-- 1.3.6.1.4.1.10106.3.101291.1.1.137
		had3000c01v1Grp4P1ADelay OBJECT-TYPE
			SYNTAX Uint8
			MAX-ACCESS read-write
			STATUS current
			DESCRIPTION
				"Group 4 pair 1 delay"
		::= { had3000c01v1Entry 137 }

		-- 1.3.6.1.4.1.10106.3.101291.1.1.139
		had3000c01v1Grp1P0BDelay OBJECT-TYPE
			SYNTAX Uint8
			MAX-ACCESS read-write
			STATUS current
			DESCRIPTION
				"Group 1 pair 0 delay"
		::= { had3000c01v1Entry 139 }

		-- 1.3.6.1.4.1.10106.3.101291.1.1.141
		had3000c01v1Grp1P1BDelay OBJECT-TYPE
			SYNTAX Uint8
			MAX-ACCESS read-write
			STATUS current
			DESCRIPTION
				"Group 1 pair 1 delay"
		::= { had3000c01v1Entry 141 }

		-- 1.3.6.1.4.1.10106.3.101291.1.1.143
		had3000c01v1Grp2P0BDelay OBJECT-TYPE
			SYNTAX Uint8
			MAX-ACCESS read-write
			STATUS current
			DESCRIPTION
				"Group 2 pair 0 delay"
		::= { had3000c01v1Entry 143 }

		-- 1.3.6.1.4.1.10106.3.101291.1.1.145
		had3000c01v1Grp2P1BDelay OBJECT-TYPE
			SYNTAX Uint8
			MAX-ACCESS read-write
			STATUS current
			DESCRIPTION
				"Group 2 pair 1 delay"
		::= { had3000c01v1Entry 145 }

		-- 1.3.6.1.4.1.10106.3.101291.1.1.147
		had3000c01v1Grp3P0BDelay OBJECT-TYPE
			SYNTAX Uint8
			MAX-ACCESS read-write
			STATUS current
			DESCRIPTION
				"Group 3 pair 0 delay"
		::= { had3000c01v1Entry 147 }

		-- 1.3.6.1.4.1.10106.3.101291.1.1.149
		had3000c01v1Grp3P1BDelay OBJECT-TYPE
			SYNTAX Uint8
			MAX-ACCESS read-write
			STATUS current
			DESCRIPTION
				"Group 3 pair 1 delay"
		::= { had3000c01v1Entry 149 }

		-- 1.3.6.1.4.1.10106.3.101291.1.1.151
		had3000c01v1Grp4P0BDelay OBJECT-TYPE
			SYNTAX Uint8
			MAX-ACCESS read-write
			STATUS current
			DESCRIPTION
				"Group 4 pair 0 delay"
		::= { had3000c01v1Entry 151 }

		-- 1.3.6.1.4.1.10106.3.101291.1.1.153
		had3000c01v1Grp4P1BDelay OBJECT-TYPE
			SYNTAX Uint8
			MAX-ACCESS read-write
			STATUS current
			DESCRIPTION
				"Group 4 pair 1 delay"
		::= { had3000c01v1Entry 153 }

		-- 1.3.6.1.4.1.10106.3.101291.1.1.155
		had3000c01v1Aes1ADelay OBJECT-TYPE
			SYNTAX Uint8
			MAX-ACCESS read-write
			STATUS current
			DESCRIPTION
				"STRM1 delay"
		::= { had3000c01v1Entry 155 }

		-- 1.3.6.1.4.1.10106.3.101291.1.1.157
		had3000c01v1Aes2ADelay OBJECT-TYPE
			SYNTAX Uint8
			MAX-ACCESS read-write
			STATUS current
			DESCRIPTION
				"STRM2 delay"
		::= { had3000c01v1Entry 157 }

		-- 1.3.6.1.4.1.10106.3.101291.1.1.159
		had3000c01v1Aes1BDelay OBJECT-TYPE
			SYNTAX Uint8
			MAX-ACCESS read-write
			STATUS current
			DESCRIPTION
				"STRM1 delay"
		::= { had3000c01v1Entry 159 }

		-- 1.3.6.1.4.1.10106.3.101291.1.1.161
		had3000c01v1Aes2BDelay OBJECT-TYPE
			SYNTAX Uint8
			MAX-ACCESS read-write
			STATUS current
			DESCRIPTION
				"STRM2 delay"
		::= { had3000c01v1Entry 161 }

		-- 1.3.6.1.4.1.10106.3.101291.1.1.163
		had3000c01v1NoSignalA OBJECT-TYPE
			SYNTAX BitFail
			MAX-ACCESS read-only
			STATUS current
			DESCRIPTION
				"There is no SDI signal or the format is not supported"
		::= { had3000c01v1Entry 163 }

		-- 1.3.6.1.4.1.10106.3.101291.1.1.164
		had3000c01v1NoSignalATrapEnable OBJECT-TYPE
			SYNTAX AlarmEnable
			MAX-ACCESS read-write
			STATUS current
			DESCRIPTION
				"There is no SDI signal or the format is not supported Trap Enable"
		::= { had3000c01v1Entry 164 }

		-- 1.3.6.1.4.1.10106.3.101291.1.1.165
		had3000c01v1UnlockA OBJECT-TYPE
			SYNTAX BitFail
			MAX-ACCESS read-only
			STATUS current
			DESCRIPTION
				"Indicates signal unlock fail"
		::= { had3000c01v1Entry 165 }

		-- 1.3.6.1.4.1.10106.3.101291.1.1.166
		had3000c01v1UnlockATrapEnable OBJECT-TYPE
			SYNTAX AlarmEnable
			MAX-ACCESS read-write
			STATUS current
			DESCRIPTION
				"Indicates signal unlock fail Trap Enable"
		::= { had3000c01v1Entry 166 }

		-- 1.3.6.1.4.1.10106.3.101291.1.1.167
		had3000c01v1EdhErrorA OBJECT-TYPE
			SYNTAX BitFail
			MAX-ACCESS read-only
			STATUS current
			DESCRIPTION
				"There are EDH/CRC errors on SDI signal"
		::= { had3000c01v1Entry 167 }

		-- 1.3.6.1.4.1.10106.3.101291.1.1.168
		had3000c01v1EdhErrorATrapEnable OBJECT-TYPE
			SYNTAX AlarmEnable
			MAX-ACCESS read-write
			STATUS current
			DESCRIPTION
				"There are EDH/CRC errors on SDI signal Trap Enable"
		::= { had3000c01v1Entry 168 }

		-- 1.3.6.1.4.1.10106.3.101291.1.1.169
		had3000c01v1SampRFailA OBJECT-TYPE
			SYNTAX BitFail
			MAX-ACCESS read-only
			STATUS current
			DESCRIPTION
				"Indicates sampling rate fail"
		::= { had3000c01v1Entry 169 }

		-- 1.3.6.1.4.1.10106.3.101291.1.1.170
		had3000c01v1SampRFailATrapEnable OBJECT-TYPE
			SYNTAX AlarmEnable
			MAX-ACCESS read-write
			STATUS current
			DESCRIPTION
				"Indicates sampling rate fail Trap Enable"
		::= { had3000c01v1Entry 170 }

		-- 1.3.6.1.4.1.10106.3.101291.1.1.171
		had3000c01v1DeemFailA OBJECT-TYPE
			SYNTAX BitFail
			MAX-ACCESS read-only
			STATUS current
			DESCRIPTION
				"There is no valid deembedded audio"
		::= { had3000c01v1Entry 171 }

		-- 1.3.6.1.4.1.10106.3.101291.1.1.172
		had3000c01v1DeemFailATrapEnable OBJECT-TYPE
			SYNTAX AlarmEnable
			MAX-ACCESS read-write
			STATUS current
			DESCRIPTION
				"There is no valid deembedded audio Trap Enable"
		::= { had3000c01v1Entry 172 }

		-- 1.3.6.1.4.1.10106.3.101291.1.1.173
		had3000c01v1AesOvlA OBJECT-TYPE
			SYNTAX BitFail
			MAX-ACCESS read-only
			STATUS current
			DESCRIPTION
				"There is overload or silence in analog outputs"
		::= { had3000c01v1Entry 173 }

		-- 1.3.6.1.4.1.10106.3.101291.1.1.174
		had3000c01v1AesOvlATrapEnable OBJECT-TYPE
			SYNTAX AlarmEnable
			MAX-ACCESS read-write
			STATUS current
			DESCRIPTION
				"There is overload or silence in analog outputs Trap Enable"
		::= { had3000c01v1Entry 174 }

		-- 1.3.6.1.4.1.10106.3.101291.1.1.175
		had3000c01v1DeemOvlA OBJECT-TYPE
			SYNTAX BitFail
			MAX-ACCESS read-only
			STATUS current
			DESCRIPTION
				"There is overload or silence in embed audio"
		::= { had3000c01v1Entry 175 }

		-- 1.3.6.1.4.1.10106.3.101291.1.1.176
		had3000c01v1DeemOvlATrapEnable OBJECT-TYPE
			SYNTAX AlarmEnable
			MAX-ACCESS read-write
			STATUS current
			DESCRIPTION
				"There is overload or silence in embed audio Trap Enable"
		::= { had3000c01v1Entry 176 }

		-- 1.3.6.1.4.1.10106.3.101291.1.1.177
		had3000c01v1FormatA OBJECT-TYPE
			SYNTAX SdiHd3gFmt3
			MAX-ACCESS read-only
			STATUS current
			DESCRIPTION
				"Indicates the SDI transmited signal format"
		::= { had3000c01v1Entry 177 }

		-- 1.3.6.1.4.1.10106.3.101291.1.1.179
		had3000c01v1NoSignalB OBJECT-TYPE
			SYNTAX BitFail
			MAX-ACCESS read-only
			STATUS current
			DESCRIPTION
				"There is no SDI signal or the format is not supported"
		::= { had3000c01v1Entry 179 }

		-- 1.3.6.1.4.1.10106.3.101291.1.1.180
		had3000c01v1NoSignalBTrapEnable OBJECT-TYPE
			SYNTAX AlarmEnable
			MAX-ACCESS read-write
			STATUS current
			DESCRIPTION
				"There is no SDI signal or the format is not supported Trap Enable"
		::= { had3000c01v1Entry 180 }

		-- 1.3.6.1.4.1.10106.3.101291.1.1.181
		had3000c01v1UnlockB OBJECT-TYPE
			SYNTAX BitFail
			MAX-ACCESS read-only
			STATUS current
			DESCRIPTION
				"Indicates signal unlock fail"
		::= { had3000c01v1Entry 181 }

		-- 1.3.6.1.4.1.10106.3.101291.1.1.182
		had3000c01v1UnlockBTrapEnable OBJECT-TYPE
			SYNTAX AlarmEnable
			MAX-ACCESS read-write
			STATUS current
			DESCRIPTION
				"Indicates signal unlock fail Trap Enable"
		::= { had3000c01v1Entry 182 }

		-- 1.3.6.1.4.1.10106.3.101291.1.1.183
		had3000c01v1EdhErrorB OBJECT-TYPE
			SYNTAX BitFail
			MAX-ACCESS read-only
			STATUS current
			DESCRIPTION
				"There are EDH/CRC errors on SDI signal"
		::= { had3000c01v1Entry 183 }

		-- 1.3.6.1.4.1.10106.3.101291.1.1.184
		had3000c01v1EdhErrorBTrapEnable OBJECT-TYPE
			SYNTAX AlarmEnable
			MAX-ACCESS read-write
			STATUS current
			DESCRIPTION
				"There are EDH/CRC errors on SDI signal Trap Enable"
		::= { had3000c01v1Entry 184 }

		-- 1.3.6.1.4.1.10106.3.101291.1.1.185
		had3000c01v1SampRFailB OBJECT-TYPE
			SYNTAX BitFail
			MAX-ACCESS read-only
			STATUS current
			DESCRIPTION
				"Indicates sampling rate fail"
		::= { had3000c01v1Entry 185 }

		-- 1.3.6.1.4.1.10106.3.101291.1.1.186
		had3000c01v1SampRFailBTrapEnable OBJECT-TYPE
			SYNTAX AlarmEnable
			MAX-ACCESS read-write
			STATUS current
			DESCRIPTION
				"Indicates sampling rate fail Trap Enable"
		::= { had3000c01v1Entry 186 }

		-- 1.3.6.1.4.1.10106.3.101291.1.1.187
		had3000c01v1DeemFailB OBJECT-TYPE
			SYNTAX BitFail
			MAX-ACCESS read-only
			STATUS current
			DESCRIPTION
				"There is no valid deembedded audio"
		::= { had3000c01v1Entry 187 }

		-- 1.3.6.1.4.1.10106.3.101291.1.1.188
		had3000c01v1DeemFailBTrapEnable OBJECT-TYPE
			SYNTAX AlarmEnable
			MAX-ACCESS read-write
			STATUS current
			DESCRIPTION
				"There is no valid deembedded audio Trap Enable"
		::= { had3000c01v1Entry 188 }

		-- 1.3.6.1.4.1.10106.3.101291.1.1.189
		had3000c01v1AesOvlB OBJECT-TYPE
			SYNTAX BitFail
			MAX-ACCESS read-only
			STATUS current
			DESCRIPTION
				"There is overload or silence in analog outputs"
		::= { had3000c01v1Entry 189 }

		-- 1.3.6.1.4.1.10106.3.101291.1.1.190
		had3000c01v1AesOvlBTrapEnable OBJECT-TYPE
			SYNTAX AlarmEnable
			MAX-ACCESS read-write
			STATUS current
			DESCRIPTION
				"There is overload or silence in analog outputs Trap Enable"
		::= { had3000c01v1Entry 190 }

		-- 1.3.6.1.4.1.10106.3.101291.1.1.191
		had3000c01v1DeemOvlB OBJECT-TYPE
			SYNTAX BitFail
			MAX-ACCESS read-only
			STATUS current
			DESCRIPTION
				"There is overload or silence in embed audio"
		::= { had3000c01v1Entry 191 }

		-- 1.3.6.1.4.1.10106.3.101291.1.1.192
		had3000c01v1DeemOvlBTrapEnable OBJECT-TYPE
			SYNTAX AlarmEnable
			MAX-ACCESS read-write
			STATUS current
			DESCRIPTION
				"There is overload or silence in embed audio Trap Enable"
		::= { had3000c01v1Entry 192 }

		-- 1.3.6.1.4.1.10106.3.101291.1.1.193
		had3000c01v1FormatB OBJECT-TYPE
			SYNTAX SdiHd3gFmt3
			MAX-ACCESS read-only
			STATUS current
			DESCRIPTION
				"Indicates the SDI transmited signal format"
		::= { had3000c01v1Entry 193 }

		-- 1.3.6.1.4.1.10106.3.101291.1.1.195
		had3000c01v1SerialNo OBJECT-TYPE
			SYNTAX SerialNo
			MAX-ACCESS read-only
			STATUS current
			DESCRIPTION
				"Serial number"
		::= { had3000c01v1Entry 195 }

		-- 1.3.6.1.4.1.10106.3.101291.1.1.215
		had3000c01v1CorteSelChB OBJECT-TYPE
			SYNTAX Bit0BlBit1Cut
			MAX-ACCESS read-write
			STATUS current
			DESCRIPTION
				"Selects the action to perform when the input signal is absent"
		::= { had3000c01v1Entry 215 }

		-- 1.3.6.1.4.1.10106.3.362001
		ipa3000c01v1 OBJECT IDENTIFIER ::= { albalaProducts 362001 }

		-- 1.3.6.1.4.1.10106.3.362001.1
		ipa3000c01v1Table  OBJECT-TYPE
			SYNTAX SEQUENCE OF Ipa3000c01v1Entry
			MAX-ACCESS not-accessible
			STATUS current
			DESCRIPTION
				"Module  IPA3000C01V1 Table"
			::= { ipa3000c01v1 1 }

		-- 1.3.6.1.4.1.10106.3.362001.1.1
		ipa3000c01v1Entry  OBJECT-TYPE
			SYNTAX Ipa3000c01v1Entry
			MAX-ACCESS not-accessible
			STATUS current
			DESCRIPTION
				"Module IPA3000C01V1 Entry"
			INDEX { ipa3000c01v1Index }
			::= { ipa3000c01v1Table 1 }

			Ipa3000c01v1Entry ::=
			SEQUENCE {
				ipa3000c01v1Index
				ModuleIndex,
				ipa3000c01v1Mode
				ChgOverMode2,
				ipa3000c01v1ModeTrapEnable
				AlarmEnable,
				ipa3000c01v1DvbTMode
				Bit0No1Yes,
				ipa3000c01v1DvbTModeTrapEnable
				AlarmEnable,
				ipa3000c01v1NarrowPllBw
				Bit0No1Yes,
				ipa3000c01v1Buzzer
				BitMask,
				ipa3000c01v1SeamlessPrior
				Bit0No1Yes,
				ipa3000c01v1Input
				ChgOverInput3,
				ipa3000c01v1InputTrapEnable
				AlarmEnable,
				ipa3000c01v1InputStChange
				Bit0No1Yes,
				ipa3000c01v1InputChange
				Bit0No1Yes,
				ipa3000c01v1EnaAsiMain
				BitMask,
				ipa3000c01v1EnaAsiRes
				BitMask,
				ipa3000c01v1EnaIpMain
				BitMask,
				ipa3000c01v1EnaIpRes
				BitMask,
				ipa3000c01v1OutDelay
				DelayX100Ns,
				ipa3000c01v1OutDelayTrapEnable
				AlarmEnable,
				ipa3000c01v1AsiMainPrior
				Uint2,
				ipa3000c01v1AsiResPrior
				Uint2,
				ipa3000c01v1IpMainPrior
				Uint2,
				ipa3000c01v1IpResPrior
				Uint2,
				ipa3000c01v1StatReset
				Bit0No1Yes,
				ipa3000c01v1StatSel
				Bit0Ipm1Ipr,
				ipa3000c01v1StatMode
				Bit01s1Total,
				ipa3000c01v1IgmpVersion
				Bit0V21V3,
				ipa3000c01v1EthMode
				EthMode,
				ipa3000c01v1PingEnable
				Bit0No1Yes,
				ipa3000c01v1PacketDelay
				DelayPacket1,
				ipa3000c01v1Str1UipDAdd3
				Uint8,
				ipa3000c01v1Str1UipDAdd2
				Uint8,
				ipa3000c01v1Str1UipDAdd1
				Uint8,
				ipa3000c01v1Str1UipDAdd0
				Uint8,
				ipa3000c01v1Str1MipDAdd3
				Uint8,
				ipa3000c01v1Str1MipDAdd2
				Uint8,
				ipa3000c01v1Str1MipDAdd1
				Uint8,
				ipa3000c01v1Str1MipDAdd0
				Uint8,
				ipa3000c01v1Str1DPortMsb
				Uint8,
				ipa3000c01v1Str1DPortLsb
				Uint8,
				ipa3000c01v1Str1FecEna
				Bit0No1Yes,
				ipa3000c01v1Str1MulticEna
				IpaTxMode,
				ipa3000c01v1VlanRx1Enable
				Bit0No1Yes,
				ipa3000c01v1VlanRx1Reg1
				Uint8,
				ipa3000c01v1VlanRx1Reg2
				Uint8,
				ipa3000c01v1Str2UipDAdd3
				Uint8,
				ipa3000c01v1Str2UipDAdd2
				Uint8,
				ipa3000c01v1Str2UipDAdd1
				Uint8,
				ipa3000c01v1Str2UipDAdd0
				Uint8,
				ipa3000c01v1Str2MipDAdd3
				Uint8,
				ipa3000c01v1Str2MipDAdd2
				Uint8,
				ipa3000c01v1Str2MipDAdd1
				Uint8,
				ipa3000c01v1Str2MipDAdd0
				Uint8,
				ipa3000c01v1Str2DPortMsb
				Uint8,
				ipa3000c01v1Str2DPortLsb
				Uint8,
				ipa3000c01v1Str2FecEna
				Bit0No1Yes,
				ipa3000c01v1Str2MulticEna
				IpaTxMode,
				ipa3000c01v1VlanRx2Enable
				Bit0No1Yes,
				ipa3000c01v1VlanRx2Reg1
				Uint8,
				ipa3000c01v1VlanRx2Reg2
				Uint8,
				ipa3000c01v1TxUniEna
				Bit0No1Yes,
				ipa3000c01v1TxMultiEna
				IpaTxMode,
				ipa3000c01v1LocalIpAdd3
				Uint8,
				ipa3000c01v1LocalIpAdd2
				Uint8,
				ipa3000c01v1LocalIpAdd1
				Uint8,
				ipa3000c01v1LocalIpAdd0
				Uint8,
				ipa3000c01v1LocalIpMask3
				Uint8,
				ipa3000c01v1LocalIpMask2
				Uint8,
				ipa3000c01v1LocalIpMask1
				Uint8,
				ipa3000c01v1LocalIpMask0
				Uint8,
				ipa3000c01v1LocalIpGway3
				Uint8,
				ipa3000c01v1LocalIpGway2
				Uint8,
				ipa3000c01v1LocalIpGway1
				Uint8,
				ipa3000c01v1LocalIpGway0
				Uint8,
				ipa3000c01v1TxUipAdd3
				Uint8,
				ipa3000c01v1TxUipAdd2
				Uint8,
				ipa3000c01v1TxUipAdd1
				Uint8,
				ipa3000c01v1TxUipAdd0
				Uint8,
				ipa3000c01v1TxMipAdd3
				Uint8,
				ipa3000c01v1TxMipAdd2
				Uint8,
				ipa3000c01v1TxMipAdd1
				Uint8,
				ipa3000c01v1TxMipAdd0
				Uint8,
				ipa3000c01v1TxSPortMsb
				Uint8,
				ipa3000c01v1TxSPortLsb
				Uint8,
				ipa3000c01v1TxDPortMsb
				Uint8,
				ipa3000c01v1TxDPortLsb
				Uint8,
				ipa3000c01v1VlanTxEnable
				Bit0No1Yes,
				ipa3000c01v1VlanTxPriority
				Uint3,
				ipa3000c01v1VlanTxReg1
				Uint8,
				ipa3000c01v1VlanTxReg2
				Uint8,
				ipa3000c01v1TxLParam
				Uint5,
				ipa3000c01v1TxFecMode
				FecMode,
				ipa3000c01v1TxDParam
				Uint5,
				ipa3000c01v1TxTspkInIppk
				Uint3,
				ipa3000c01v1TxRowDelay
				Uint5,
				ipa3000c01v1TxColDelay
				Uint8,
				ipa3000c01v1LowCost
				Bit0No1Yes,
				ipa3000c01v1HighReliabilty
				Bit0No1Yes,
				ipa3000c01v1HighThroughput
				Bit0No1Yes,
				ipa3000c01v1LowDelay
				Bit0No1Yes,
				ipa3000c01v1Precedence
				IpaPrecedence,
				ipa3000c01v1Ttl
				Uint8,
				ipa3000c01v11ppsFail
				BitFail,
				ipa3000c01v11ppsFailTrapEnable
				AlarmEnable,
				ipa3000c01v110mhzFail
				BitFail,
				ipa3000c01v110mhzFailTrapEnable
				AlarmEnable,
				ipa3000c01v1OutputFail
				BitFail,
				ipa3000c01v1OutputFailTrapEnable
				AlarmEnable,
				ipa3000c01v1AsiMainDelWar
				BitFail,
				ipa3000c01v1AsiMainDelWarTrapEnable
				AlarmEnable,
				ipa3000c01v1AsiResDelWar
				BitFail,
				ipa3000c01v1AsiResDelWarTrapEnable
				AlarmEnable,
				ipa3000c01v1IpMainDelWar
				BitFail,
				ipa3000c01v1IpMainDelWarTrapEnable
				AlarmEnable,
				ipa3000c01v1IpResDelWar
				BitFail,
				ipa3000c01v1IpResDelWarTrapEnable
				AlarmEnable,
				ipa3000c01v1AsiMainFail
				BitFail,
				ipa3000c01v1AsiMainFailTrapEnable
				AlarmEnable,
				ipa3000c01v1ExAsiMainFail
				BitFail,
				ipa3000c01v1ExAsiMainFailTrapEnable
				AlarmEnable,
				ipa3000c01v1AsiResFail
				BitFail,
				ipa3000c01v1AsiResFailTrapEnable
				AlarmEnable,
				ipa3000c01v1ExAsiResFail
				BitFail,
				ipa3000c01v1ExAsiResFailTrapEnable
				AlarmEnable,
				ipa3000c01v1IpMainFail
				BitFail,
				ipa3000c01v1IpMainFailTrapEnable
				AlarmEnable,
				ipa3000c01v1ExIpMainFail
				BitFail,
				ipa3000c01v1ExIpMainFailTrapEnable
				AlarmEnable,
				ipa3000c01v1IpResFail
				BitFail,
				ipa3000c01v1IpResFailTrapEnable
				AlarmEnable,
				ipa3000c01v1ExIpResFail
				BitFail,
				ipa3000c01v1ExIpResFailTrapEnable
				AlarmEnable,
				ipa3000c01v1AsimAsirSeam
				Bit0Sea1Nse,
				ipa3000c01v1AsimIpmSeam
				Bit0Sea1Nse,
				ipa3000c01v1AsimIprSeam
				Bit0Sea1Nse,
				ipa3000c01v1AsirIpmSeam
				Bit0Sea1Nse,
				ipa3000c01v1AsirIprSeam
				Bit0Sea1Nse,
				ipa3000c01v1IpmIprSeam
				Bit0Sea1Nse,
				ipa3000c01v1GlobalSeam
				Bit0Sea1Nse,
				ipa3000c01v1GlobalSeamTrapEnable
				AlarmEnable,
				ipa3000c01v1AsiMainDelay
				DelayX65Ms,
				ipa3000c01v1AsiResDelay
				DelayX65Ms,
				ipa3000c01v1IpMainDelay
				DelayX65Ms,
				ipa3000c01v1IpResDelay
				DelayX65Ms,
				ipa3000c01v1IpRxAddress3
				Uint8,
				ipa3000c01v1IpRxAddress2
				Uint8,
				ipa3000c01v1IpRxAddress1
				Uint8,
				ipa3000c01v1IpRxAddress0
				Uint8,
				ipa3000c01v1IpRxPort
				Uint16,
				ipa3000c01v1LParam
				Uint5,
				ipa3000c01v1FecMode
				FecMode,
				ipa3000c01v1PacketSize
				Bit02041188,
				ipa3000c01v1DParam
				Uint5,
				ipa3000c01v1TsPckInIpPck
				Uint3,
				ipa3000c01v1PacketRate
				PacketRate,
				ipa3000c01v1TimeSinceReset
				TimeS4,
				ipa3000c01v1LostIpPck
				Uint16,
				ipa3000c01v1RecoveredIpPck
				Uint16,
				ipa3000c01v1OutOrdIpPck
				Uint16,
				ipa3000c01v1FecRate
				PacketRate,
				ipa3000c01v1Link
				IpaEtherStat,
				ipa3000c01v1DestAvailable
				Bit0No1Yes,
				ipa3000c01v1BufferStatus
				Rate1,
				ipa3000c01v1PingStatus
				IpaPingStat,
				ipa3000c01v1SerialNo
				SerialNo,
				ipa3000c01v1NullPckRtp
				Bit0No1Yes,
				ipa3000c01v1Str1IgmFAdd3
				Uint8,
				ipa3000c01v1Str1IgmFAdd2
				Uint8,
				ipa3000c01v1Str1IgmFAdd1
				Uint8,
				ipa3000c01v1Str1IgmFAdd0
				Uint8,
				ipa3000c01v1Str2IgmFAdd3
				Uint8,
				ipa3000c01v1Str2IgmFAdd2
				Uint8,
				ipa3000c01v1Str2IgmFAdd1
				Uint8,
				ipa3000c01v1Str2IgmFAdd0
				Uint8,
				ipa3000c01v1EnSeamNondvbt
				Bit0No1Yes,
				ipa3000c01v1IpLinkFailEn
				Bit0No1Yes,
				ipa3000c01v1IpDestFailEn
				Bit0No1Yes,
				ipa3000c01v1System
				IpaEtherSys,
				ipa3000c01v1SpeedForce
				Bit0Ann1For,
				ipa3000c01v1BadCrcPck
				Uint16,
				ipa3000c01v1InpFailMode
				Bit0Yes1No,
				ipa3000c01v1MaxDelayTxIp
				TimeX10Ms
			 }

		-- 1.3.6.1.4.1.10106.3.101291.1.1.1
		ipa3000c01v1Index OBJECT-TYPE
			SYNTAX ModuleIndex
			MAX-ACCESS read-only
			STATUS current
			DESCRIPTION
				"Index of IPA3000C01V1 Table"
		::= { ipa3000c01v1Entry 1 }

		-- 1.3.6.1.4.1.10106.3.101291.1.1.3
		ipa3000c01v1Mode OBJECT-TYPE
			SYNTAX ChgOverMode2
			MAX-ACCESS read-write
			STATUS current
			DESCRIPTION
				"Allows selecting the switching mode"
		::= { ipa3000c01v1Entry 3 }

		-- 1.3.6.1.4.1.10106.3.101291.1.1.4
		ipa3000c01v1ModeTrapEnable OBJECT-TYPE
			SYNTAX AlarmEnable
			MAX-ACCESS read-write
			STATUS current
			DESCRIPTION
				"Allows selecting the switching mode Trap Enable"
		::= { ipa3000c01v1Entry 4 }

		-- 1.3.6.1.4.1.10106.3.101291.1.1.5
		ipa3000c01v1DvbTMode OBJECT-TYPE
			SYNTAX Bit0No1Yes
			MAX-ACCESS read-write
			STATUS current
			DESCRIPTION
				"Selects DVB-T mode."
		::= { ipa3000c01v1Entry 5 }

		-- 1.3.6.1.4.1.10106.3.101291.1.1.6
		ipa3000c01v1DvbTModeTrapEnable OBJECT-TYPE
			SYNTAX AlarmEnable
			MAX-ACCESS read-write
			STATUS current
			DESCRIPTION
				"Selects DVB-T mode. Trap Enable"
		::= { ipa3000c01v1Entry 6 }

		-- 1.3.6.1.4.1.10106.3.101291.1.1.7
		ipa3000c01v1NarrowPllBw OBJECT-TYPE
			SYNTAX Bit0No1Yes
			MAX-ACCESS read-write
			STATUS current
			DESCRIPTION
				"Allows selecting a narrow PLL bandwidth in the clock packet PLL in non DVB-T mode to achieve a very stable bitrate"
		::= { ipa3000c01v1Entry 7 }

		-- 1.3.6.1.4.1.10106.3.101291.1.1.9
		ipa3000c01v1Buzzer OBJECT-TYPE
			SYNTAX BitMask
			MAX-ACCESS read-write
			STATUS current
			DESCRIPTION
				"Allows buzzer operation"
		::= { ipa3000c01v1Entry 9 }

		-- 1.3.6.1.4.1.10106.3.101291.1.1.11
		ipa3000c01v1SeamlessPrior OBJECT-TYPE
			SYNTAX Bit0No1Yes
			MAX-ACCESS read-write
			STATUS current
			DESCRIPTION
				"Selects if seamless status has priority over input priority in hafl-auto mode"
		::= { ipa3000c01v1Entry 11 }

		-- 1.3.6.1.4.1.10106.3.101291.1.1.13
		ipa3000c01v1Input OBJECT-TYPE
			SYNTAX ChgOverInput3
			MAX-ACCESS read-write
			STATUS current
			DESCRIPTION
				"Selected input"
		::= { ipa3000c01v1Entry 13 }

		-- 1.3.6.1.4.1.10106.3.101291.1.1.14
		ipa3000c01v1InputTrapEnable OBJECT-TYPE
			SYNTAX AlarmEnable
			MAX-ACCESS read-write
			STATUS current
			DESCRIPTION
				"Selected input Trap Enable"
		::= { ipa3000c01v1Entry 14 }

		-- 1.3.6.1.4.1.10106.3.101291.1.1.15
		ipa3000c01v1InputStChange OBJECT-TYPE
			SYNTAX Bit0No1Yes
			MAX-ACCESS read-write
			STATUS current
			DESCRIPTION
				"Signals a change in fail status"
		::= { ipa3000c01v1Entry 15 }

		-- 1.3.6.1.4.1.10106.3.101291.1.1.17
		ipa3000c01v1InputChange OBJECT-TYPE
			SYNTAX Bit0No1Yes
			MAX-ACCESS read-write
			STATUS current
			DESCRIPTION
				"Signals a change in selected input"
		::= { ipa3000c01v1Entry 17 }

		-- 1.3.6.1.4.1.10106.3.101291.1.1.19
		ipa3000c01v1EnaAsiMain OBJECT-TYPE
			SYNTAX BitMask
			MAX-ACCESS read-write
			STATUS current
			DESCRIPTION
				"Allows disabling ASI main input when it is not used"
		::= { ipa3000c01v1Entry 19 }

		-- 1.3.6.1.4.1.10106.3.101291.1.1.21
		ipa3000c01v1EnaAsiRes OBJECT-TYPE
			SYNTAX BitMask
			MAX-ACCESS read-write
			STATUS current
			DESCRIPTION
				"Allows disabling ASI reserve input when it is not used"
		::= { ipa3000c01v1Entry 21 }

		-- 1.3.6.1.4.1.10106.3.101291.1.1.23
		ipa3000c01v1EnaIpMain OBJECT-TYPE
			SYNTAX BitMask
			MAX-ACCESS read-write
			STATUS current
			DESCRIPTION
				"Allows disabling IP main input when it is not used"
		::= { ipa3000c01v1Entry 23 }

		-- 1.3.6.1.4.1.10106.3.101291.1.1.25
		ipa3000c01v1EnaIpRes OBJECT-TYPE
			SYNTAX BitMask
			MAX-ACCESS read-write
			STATUS current
			DESCRIPTION
				"Allows disabling IP reserver input when it is not used"
		::= { ipa3000c01v1Entry 25 }

		-- 1.3.6.1.4.1.10106.3.101291.1.1.27
		ipa3000c01v1OutDelay OBJECT-TYPE
			SYNTAX DelayX100Ns
			MAX-ACCESS read-write
			STATUS current
			DESCRIPTION
				"Output delay refered to 1PPS reference in DVB-T mode"
		::= { ipa3000c01v1Entry 27 }

		-- 1.3.6.1.4.1.10106.3.101291.1.1.28
		ipa3000c01v1OutDelayTrapEnable OBJECT-TYPE
			SYNTAX AlarmEnable
			MAX-ACCESS read-write
			STATUS current
			DESCRIPTION
				"Output delay refered to 1PPS reference in DVB-T mode Trap Enable"
		::= { ipa3000c01v1Entry 28 }

		-- 1.3.6.1.4.1.10106.3.101291.1.1.29
		ipa3000c01v1AsiMainPrior OBJECT-TYPE
			SYNTAX Uint2
			MAX-ACCESS read-write
			STATUS current
			DESCRIPTION
				"Allows selecting the ASI main input priority"
		::= { ipa3000c01v1Entry 29 }

		-- 1.3.6.1.4.1.10106.3.101291.1.1.31
		ipa3000c01v1AsiResPrior OBJECT-TYPE
			SYNTAX Uint2
			MAX-ACCESS read-write
			STATUS current
			DESCRIPTION
				"Allows selecting the ASI reserve input priority"
		::= { ipa3000c01v1Entry 31 }

		-- 1.3.6.1.4.1.10106.3.101291.1.1.33
		ipa3000c01v1IpMainPrior OBJECT-TYPE
			SYNTAX Uint2
			MAX-ACCESS read-write
			STATUS current
			DESCRIPTION
				"Allows selecting the IP main input priority"
		::= { ipa3000c01v1Entry 33 }

		-- 1.3.6.1.4.1.10106.3.101291.1.1.35
		ipa3000c01v1IpResPrior OBJECT-TYPE
			SYNTAX Uint2
			MAX-ACCESS read-write
			STATUS current
			DESCRIPTION
				"Allows selecting the IP reserve input priority"
		::= { ipa3000c01v1Entry 35 }

		-- 1.3.6.1.4.1.10106.3.101291.1.1.37
		ipa3000c01v1StatReset OBJECT-TYPE
			SYNTAX Bit0No1Yes
			MAX-ACCESS read-write
			STATUS current
			DESCRIPTION
				"Allows reseting the statistics measurements"
		::= { ipa3000c01v1Entry 37 }

		-- 1.3.6.1.4.1.10106.3.101291.1.1.39
		ipa3000c01v1StatSel OBJECT-TYPE
			SYNTAX Bit0Ipm1Ipr
			MAX-ACCESS read-write
			STATUS current
			DESCRIPTION
				"Allows selecting the channel to be displayed"
		::= { ipa3000c01v1Entry 39 }

		-- 1.3.6.1.4.1.10106.3.101291.1.1.41
		ipa3000c01v1StatMode OBJECT-TYPE
			SYNTAX Bit01s1Total
			MAX-ACCESS read-write
			STATUS current
			DESCRIPTION
				"Allows selecting the statistics mode"
		::= { ipa3000c01v1Entry 41 }

		-- 1.3.6.1.4.1.10106.3.101291.1.1.43
		ipa3000c01v1IgmpVersion OBJECT-TYPE
			SYNTAX Bit0V21V3
			MAX-ACCESS read-write
			STATUS current
			DESCRIPTION
				"Allows selecting the IGMP version"
		::= { ipa3000c01v1Entry 43 }

		-- 1.3.6.1.4.1.10106.3.101291.1.1.45
		ipa3000c01v1EthMode OBJECT-TYPE
			SYNTAX EthMode
			MAX-ACCESS read-write
			STATUS current
			DESCRIPTION
				"Allows selecting the Ethernet operating mode"
		::= { ipa3000c01v1Entry 45 }

		-- 1.3.6.1.4.1.10106.3.101291.1.1.47
		ipa3000c01v1PingEnable OBJECT-TYPE
			SYNTAX Bit0No1Yes
			MAX-ACCESS read-write
			STATUS current
			DESCRIPTION
				"Allows making a periodic ping to the unicast address"
		::= { ipa3000c01v1Entry 47 }

		-- 1.3.6.1.4.1.10106.3.101291.1.1.49
		ipa3000c01v1PacketDelay OBJECT-TYPE
			SYNTAX DelayPacket1
			MAX-ACCESS read-write
			STATUS current
			DESCRIPTION
				"Output delay in TS packets in non DVB-T mode"
		::= { ipa3000c01v1Entry 49 }

		-- 1.3.6.1.4.1.10106.3.101291.1.1.51
		ipa3000c01v1Str1UipDAdd3 OBJECT-TYPE
			SYNTAX Uint8
			MAX-ACCESS read-write
			STATUS current
			DESCRIPTION
				"Unicast IP address (3)"
		::= { ipa3000c01v1Entry 51 }

		-- 1.3.6.1.4.1.10106.3.101291.1.1.53
		ipa3000c01v1Str1UipDAdd2 OBJECT-TYPE
			SYNTAX Uint8
			MAX-ACCESS read-write
			STATUS current
			DESCRIPTION
				"Unicast IP address (2)"
		::= { ipa3000c01v1Entry 53 }

		-- 1.3.6.1.4.1.10106.3.101291.1.1.55
		ipa3000c01v1Str1UipDAdd1 OBJECT-TYPE
			SYNTAX Uint8
			MAX-ACCESS read-write
			STATUS current
			DESCRIPTION
				"Unicast IP address (1)"
		::= { ipa3000c01v1Entry 55 }

		-- 1.3.6.1.4.1.10106.3.101291.1.1.57
		ipa3000c01v1Str1UipDAdd0 OBJECT-TYPE
			SYNTAX Uint8
			MAX-ACCESS read-write
			STATUS current
			DESCRIPTION
				"Unicast IP address (0)"
		::= { ipa3000c01v1Entry 57 }

		-- 1.3.6.1.4.1.10106.3.101291.1.1.59
		ipa3000c01v1Str1MipDAdd3 OBJECT-TYPE
			SYNTAX Uint8
			MAX-ACCESS read-write
			STATUS current
			DESCRIPTION
				"Multicast IP address (3)"
		::= { ipa3000c01v1Entry 59 }

		-- 1.3.6.1.4.1.10106.3.101291.1.1.61
		ipa3000c01v1Str1MipDAdd2 OBJECT-TYPE
			SYNTAX Uint8
			MAX-ACCESS read-write
			STATUS current
			DESCRIPTION
				"Multicast IP address (2)"
		::= { ipa3000c01v1Entry 61 }

		-- 1.3.6.1.4.1.10106.3.101291.1.1.63
		ipa3000c01v1Str1MipDAdd1 OBJECT-TYPE
			SYNTAX Uint8
			MAX-ACCESS read-write
			STATUS current
			DESCRIPTION
				"Multicast IP address (1)"
		::= { ipa3000c01v1Entry 63 }

		-- 1.3.6.1.4.1.10106.3.101291.1.1.65
		ipa3000c01v1Str1MipDAdd0 OBJECT-TYPE
			SYNTAX Uint8
			MAX-ACCESS read-write
			STATUS current
			DESCRIPTION
				"Multicast IP address (0)"
		::= { ipa3000c01v1Entry 65 }

		-- 1.3.6.1.4.1.10106.3.101291.1.1.67
		ipa3000c01v1Str1DPortMsb OBJECT-TYPE
			SYNTAX Uint8
			MAX-ACCESS read-write
			STATUS current
			DESCRIPTION
				"Destination port (msb)"
		::= { ipa3000c01v1Entry 67 }

		-- 1.3.6.1.4.1.10106.3.101291.1.1.69
		ipa3000c01v1Str1DPortLsb OBJECT-TYPE
			SYNTAX Uint8
			MAX-ACCESS read-write
			STATUS current
			DESCRIPTION
				"Destination port (lsb)"
		::= { ipa3000c01v1Entry 69 }

		-- 1.3.6.1.4.1.10106.3.101291.1.1.71
		ipa3000c01v1Str1FecEna OBJECT-TYPE
			SYNTAX Bit0No1Yes
			MAX-ACCESS read-write
			STATUS current
			DESCRIPTION
				"Enable FEC"
		::= { ipa3000c01v1Entry 71 }

		-- 1.3.6.1.4.1.10106.3.101291.1.1.73
		ipa3000c01v1Str1MulticEna OBJECT-TYPE
			SYNTAX IpaTxMode
			MAX-ACCESS read-write
			STATUS current
			DESCRIPTION
				"RX mode"
		::= { ipa3000c01v1Entry 73 }

		-- 1.3.6.1.4.1.10106.3.101291.1.1.75
		ipa3000c01v1VlanRx1Enable OBJECT-TYPE
			SYNTAX Bit0No1Yes
			MAX-ACCESS read-write
			STATUS current
			DESCRIPTION
				"VLAN Enable"
		::= { ipa3000c01v1Entry 75 }

		-- 1.3.6.1.4.1.10106.3.101291.1.1.77
		ipa3000c01v1VlanRx1Reg1 OBJECT-TYPE
			SYNTAX Uint8
			MAX-ACCESS read-write
			STATUS current
			DESCRIPTION
				"VLAN_REG_1"
		::= { ipa3000c01v1Entry 77 }

		-- 1.3.6.1.4.1.10106.3.101291.1.1.79
		ipa3000c01v1VlanRx1Reg2 OBJECT-TYPE
			SYNTAX Uint8
			MAX-ACCESS read-write
			STATUS current
			DESCRIPTION
				"VLAN_REG_2"
		::= { ipa3000c01v1Entry 79 }

		-- 1.3.6.1.4.1.10106.3.101291.1.1.81
		ipa3000c01v1Str2UipDAdd3 OBJECT-TYPE
			SYNTAX Uint8
			MAX-ACCESS read-write
			STATUS current
			DESCRIPTION
				"Unicast IP address (3)"
		::= { ipa3000c01v1Entry 81 }

		-- 1.3.6.1.4.1.10106.3.101291.1.1.83
		ipa3000c01v1Str2UipDAdd2 OBJECT-TYPE
			SYNTAX Uint8
			MAX-ACCESS read-write
			STATUS current
			DESCRIPTION
				"Unicast IP address (2)"
		::= { ipa3000c01v1Entry 83 }

		-- 1.3.6.1.4.1.10106.3.101291.1.1.85
		ipa3000c01v1Str2UipDAdd1 OBJECT-TYPE
			SYNTAX Uint8
			MAX-ACCESS read-write
			STATUS current
			DESCRIPTION
				"Unicast IP address (1)"
		::= { ipa3000c01v1Entry 85 }

		-- 1.3.6.1.4.1.10106.3.101291.1.1.87
		ipa3000c01v1Str2UipDAdd0 OBJECT-TYPE
			SYNTAX Uint8
			MAX-ACCESS read-write
			STATUS current
			DESCRIPTION
				"Unicast IP address (0)"
		::= { ipa3000c01v1Entry 87 }

		-- 1.3.6.1.4.1.10106.3.101291.1.1.89
		ipa3000c01v1Str2MipDAdd3 OBJECT-TYPE
			SYNTAX Uint8
			MAX-ACCESS read-write
			STATUS current
			DESCRIPTION
				"Multicast IP address (3)"
		::= { ipa3000c01v1Entry 89 }

		-- 1.3.6.1.4.1.10106.3.101291.1.1.91
		ipa3000c01v1Str2MipDAdd2 OBJECT-TYPE
			SYNTAX Uint8
			MAX-ACCESS read-write
			STATUS current
			DESCRIPTION
				"Multicast IP address (2)"
		::= { ipa3000c01v1Entry 91 }

		-- 1.3.6.1.4.1.10106.3.101291.1.1.93
		ipa3000c01v1Str2MipDAdd1 OBJECT-TYPE
			SYNTAX Uint8
			MAX-ACCESS read-write
			STATUS current
			DESCRIPTION
				"Multicast IP address (1)"
		::= { ipa3000c01v1Entry 93 }

		-- 1.3.6.1.4.1.10106.3.101291.1.1.95
		ipa3000c01v1Str2MipDAdd0 OBJECT-TYPE
			SYNTAX Uint8
			MAX-ACCESS read-write
			STATUS current
			DESCRIPTION
				"Multicast IP address (0)"
		::= { ipa3000c01v1Entry 95 }

		-- 1.3.6.1.4.1.10106.3.101291.1.1.97
		ipa3000c01v1Str2DPortMsb OBJECT-TYPE
			SYNTAX Uint8
			MAX-ACCESS read-write
			STATUS current
			DESCRIPTION
				"Destination port (msb)"
		::= { ipa3000c01v1Entry 97 }

		-- 1.3.6.1.4.1.10106.3.101291.1.1.99
		ipa3000c01v1Str2DPortLsb OBJECT-TYPE
			SYNTAX Uint8
			MAX-ACCESS read-write
			STATUS current
			DESCRIPTION
				"Destination port (lsb)"
		::= { ipa3000c01v1Entry 99 }

		-- 1.3.6.1.4.1.10106.3.101291.1.1.101
		ipa3000c01v1Str2FecEna OBJECT-TYPE
			SYNTAX Bit0No1Yes
			MAX-ACCESS read-write
			STATUS current
			DESCRIPTION
				"Enable FEC"
		::= { ipa3000c01v1Entry 101 }

		-- 1.3.6.1.4.1.10106.3.101291.1.1.103
		ipa3000c01v1Str2MulticEna OBJECT-TYPE
			SYNTAX IpaTxMode
			MAX-ACCESS read-write
			STATUS current
			DESCRIPTION
				"RX mode"
		::= { ipa3000c01v1Entry 103 }

		-- 1.3.6.1.4.1.10106.3.101291.1.1.105
		ipa3000c01v1VlanRx2Enable OBJECT-TYPE
			SYNTAX Bit0No1Yes
			MAX-ACCESS read-write
			STATUS current
			DESCRIPTION
				"VLAN Enable"
		::= { ipa3000c01v1Entry 105 }

		-- 1.3.6.1.4.1.10106.3.101291.1.1.107
		ipa3000c01v1VlanRx2Reg1 OBJECT-TYPE
			SYNTAX Uint8
			MAX-ACCESS read-write
			STATUS current
			DESCRIPTION
				"VLAN_REG_1"
		::= { ipa3000c01v1Entry 107 }

		-- 1.3.6.1.4.1.10106.3.101291.1.1.109
		ipa3000c01v1VlanRx2Reg2 OBJECT-TYPE
			SYNTAX Uint8
			MAX-ACCESS read-write
			STATUS current
			DESCRIPTION
				"VLAN_REG_2"
		::= { ipa3000c01v1Entry 109 }

		-- 1.3.6.1.4.1.10106.3.101291.1.1.111
		ipa3000c01v1TxUniEna OBJECT-TYPE
			SYNTAX Bit0No1Yes
			MAX-ACCESS read-write
			STATUS current
			DESCRIPTION
				"Enable TX"
		::= { ipa3000c01v1Entry 111 }

		-- 1.3.6.1.4.1.10106.3.101291.1.1.113
		ipa3000c01v1TxMultiEna OBJECT-TYPE
			SYNTAX IpaTxMode
			MAX-ACCESS read-write
			STATUS current
			DESCRIPTION
				"TX mode"
		::= { ipa3000c01v1Entry 113 }

		-- 1.3.6.1.4.1.10106.3.101291.1.1.115
		ipa3000c01v1LocalIpAdd3 OBJECT-TYPE
			SYNTAX Uint8
			MAX-ACCESS read-write
			STATUS current
			DESCRIPTION
				"Unicast IP address (3)"
		::= { ipa3000c01v1Entry 115 }

		-- 1.3.6.1.4.1.10106.3.101291.1.1.117
		ipa3000c01v1LocalIpAdd2 OBJECT-TYPE
			SYNTAX Uint8
			MAX-ACCESS read-write
			STATUS current
			DESCRIPTION
				"Unicast IP address (2)"
		::= { ipa3000c01v1Entry 117 }

		-- 1.3.6.1.4.1.10106.3.101291.1.1.119
		ipa3000c01v1LocalIpAdd1 OBJECT-TYPE
			SYNTAX Uint8
			MAX-ACCESS read-write
			STATUS current
			DESCRIPTION
				"Unicast IP address (1)"
		::= { ipa3000c01v1Entry 119 }

		-- 1.3.6.1.4.1.10106.3.101291.1.1.121
		ipa3000c01v1LocalIpAdd0 OBJECT-TYPE
			SYNTAX Uint8
			MAX-ACCESS read-write
			STATUS current
			DESCRIPTION
				"Unicast IP address (0)"
		::= { ipa3000c01v1Entry 121 }

		-- 1.3.6.1.4.1.10106.3.101291.1.1.123
		ipa3000c01v1LocalIpMask3 OBJECT-TYPE
			SYNTAX Uint8
			MAX-ACCESS read-write
			STATUS current
			DESCRIPTION
				"IP mask (3)"
		::= { ipa3000c01v1Entry 123 }

		-- 1.3.6.1.4.1.10106.3.101291.1.1.125
		ipa3000c01v1LocalIpMask2 OBJECT-TYPE
			SYNTAX Uint8
			MAX-ACCESS read-write
			STATUS current
			DESCRIPTION
				"IP mask (2)"
		::= { ipa3000c01v1Entry 125 }

		-- 1.3.6.1.4.1.10106.3.101291.1.1.127
		ipa3000c01v1LocalIpMask1 OBJECT-TYPE
			SYNTAX Uint8
			MAX-ACCESS read-write
			STATUS current
			DESCRIPTION
				"IP mask (1)"
		::= { ipa3000c01v1Entry 127 }

		-- 1.3.6.1.4.1.10106.3.101291.1.1.129
		ipa3000c01v1LocalIpMask0 OBJECT-TYPE
			SYNTAX Uint8
			MAX-ACCESS read-write
			STATUS current
			DESCRIPTION
				"IP mask (0)"
		::= { ipa3000c01v1Entry 129 }

		-- 1.3.6.1.4.1.10106.3.101291.1.1.131
		ipa3000c01v1LocalIpGway3 OBJECT-TYPE
			SYNTAX Uint8
			MAX-ACCESS read-write
			STATUS current
			DESCRIPTION
				"Gateway IP address (3)"
		::= { ipa3000c01v1Entry 131 }

		-- 1.3.6.1.4.1.10106.3.101291.1.1.133
		ipa3000c01v1LocalIpGway2 OBJECT-TYPE
			SYNTAX Uint8
			MAX-ACCESS read-write
			STATUS current
			DESCRIPTION
				"Gateway IP address (2)"
		::= { ipa3000c01v1Entry 133 }

		-- 1.3.6.1.4.1.10106.3.101291.1.1.135
		ipa3000c01v1LocalIpGway1 OBJECT-TYPE
			SYNTAX Uint8
			MAX-ACCESS read-write
			STATUS current
			DESCRIPTION
				"Gateway IP address (1)"
		::= { ipa3000c01v1Entry 135 }

		-- 1.3.6.1.4.1.10106.3.101291.1.1.137
		ipa3000c01v1LocalIpGway0 OBJECT-TYPE
			SYNTAX Uint8
			MAX-ACCESS read-write
			STATUS current
			DESCRIPTION
				"Gateway IP address (0)"
		::= { ipa3000c01v1Entry 137 }

		-- 1.3.6.1.4.1.10106.3.101291.1.1.139
		ipa3000c01v1TxUipAdd3 OBJECT-TYPE
			SYNTAX Uint8
			MAX-ACCESS read-write
			STATUS current
			DESCRIPTION
				"Destination IP address (3)"
		::= { ipa3000c01v1Entry 139 }

		-- 1.3.6.1.4.1.10106.3.101291.1.1.141
		ipa3000c01v1TxUipAdd2 OBJECT-TYPE
			SYNTAX Uint8
			MAX-ACCESS read-write
			STATUS current
			DESCRIPTION
				"Destination IP address (2)"
		::= { ipa3000c01v1Entry 141 }

		-- 1.3.6.1.4.1.10106.3.101291.1.1.143
		ipa3000c01v1TxUipAdd1 OBJECT-TYPE
			SYNTAX Uint8
			MAX-ACCESS read-write
			STATUS current
			DESCRIPTION
				"Destination IP address (1)"
		::= { ipa3000c01v1Entry 143 }

		-- 1.3.6.1.4.1.10106.3.101291.1.1.145
		ipa3000c01v1TxUipAdd0 OBJECT-TYPE
			SYNTAX Uint8
			MAX-ACCESS read-write
			STATUS current
			DESCRIPTION
				"Destination IP address (0)"
		::= { ipa3000c01v1Entry 145 }

		-- 1.3.6.1.4.1.10106.3.101291.1.1.147
		ipa3000c01v1TxMipAdd3 OBJECT-TYPE
			SYNTAX Uint8
			MAX-ACCESS read-write
			STATUS current
			DESCRIPTION
				"Multicast dest. IP address (3)"
		::= { ipa3000c01v1Entry 147 }

		-- 1.3.6.1.4.1.10106.3.101291.1.1.149
		ipa3000c01v1TxMipAdd2 OBJECT-TYPE
			SYNTAX Uint8
			MAX-ACCESS read-write
			STATUS current
			DESCRIPTION
				"Multicast dest. IP address (2)"
		::= { ipa3000c01v1Entry 149 }

		-- 1.3.6.1.4.1.10106.3.101291.1.1.151
		ipa3000c01v1TxMipAdd1 OBJECT-TYPE
			SYNTAX Uint8
			MAX-ACCESS read-write
			STATUS current
			DESCRIPTION
				"Multicast dest. IP address (1)"
		::= { ipa3000c01v1Entry 151 }

		-- 1.3.6.1.4.1.10106.3.101291.1.1.153
		ipa3000c01v1TxMipAdd0 OBJECT-TYPE
			SYNTAX Uint8
			MAX-ACCESS read-write
			STATUS current
			DESCRIPTION
				"Multicast dest. IP address (0)"
		::= { ipa3000c01v1Entry 153 }

		-- 1.3.6.1.4.1.10106.3.101291.1.1.155
		ipa3000c01v1TxSPortMsb OBJECT-TYPE
			SYNTAX Uint8
			MAX-ACCESS read-write
			STATUS current
			DESCRIPTION
				"Source port (msb)"
		::= { ipa3000c01v1Entry 155 }

		-- 1.3.6.1.4.1.10106.3.101291.1.1.157
		ipa3000c01v1TxSPortLsb OBJECT-TYPE
			SYNTAX Uint8
			MAX-ACCESS read-write
			STATUS current
			DESCRIPTION
				"Source port (lsb)"
		::= { ipa3000c01v1Entry 157 }

		-- 1.3.6.1.4.1.10106.3.101291.1.1.159
		ipa3000c01v1TxDPortMsb OBJECT-TYPE
			SYNTAX Uint8
			MAX-ACCESS read-write
			STATUS current
			DESCRIPTION
				"Destination port (msb)"
		::= { ipa3000c01v1Entry 159 }

		-- 1.3.6.1.4.1.10106.3.101291.1.1.161
		ipa3000c01v1TxDPortLsb OBJECT-TYPE
			SYNTAX Uint8
			MAX-ACCESS read-write
			STATUS current
			DESCRIPTION
				"Destination port (lsb)"
		::= { ipa3000c01v1Entry 161 }

		-- 1.3.6.1.4.1.10106.3.101291.1.1.163
		ipa3000c01v1VlanTxEnable OBJECT-TYPE
			SYNTAX Bit0No1Yes
			MAX-ACCESS read-write
			STATUS current
			DESCRIPTION
				"VLAN Enable"
		::= { ipa3000c01v1Entry 163 }

		-- 1.3.6.1.4.1.10106.3.101291.1.1.165
		ipa3000c01v1VlanTxPriority OBJECT-TYPE
			SYNTAX Uint3
			MAX-ACCESS read-write
			STATUS current
			DESCRIPTION
				"VLAN Priority"
		::= { ipa3000c01v1Entry 165 }

		-- 1.3.6.1.4.1.10106.3.101291.1.1.167
		ipa3000c01v1VlanTxReg1 OBJECT-TYPE
			SYNTAX Uint8
			MAX-ACCESS read-write
			STATUS current
			DESCRIPTION
				"VLAN_REG_1"
		::= { ipa3000c01v1Entry 167 }

		-- 1.3.6.1.4.1.10106.3.101291.1.1.169
		ipa3000c01v1VlanTxReg2 OBJECT-TYPE
			SYNTAX Uint8
			MAX-ACCESS read-write
			STATUS current
			DESCRIPTION
				"VLAN_REG_2"
		::= { ipa3000c01v1Entry 169 }

		-- 1.3.6.1.4.1.10106.3.101291.1.1.171
		ipa3000c01v1TxLParam OBJECT-TYPE
			SYNTAX Uint5
			MAX-ACCESS read-write
			STATUS current
			DESCRIPTION
				"L parameter (FEC mode columns)"
		::= { ipa3000c01v1Entry 171 }

		-- 1.3.6.1.4.1.10106.3.101291.1.1.173
		ipa3000c01v1TxFecMode OBJECT-TYPE
			SYNTAX FecMode
			MAX-ACCESS read-write
			STATUS current
			DESCRIPTION
				"Protocol"
		::= { ipa3000c01v1Entry 173 }

		-- 1.3.6.1.4.1.10106.3.101291.1.1.175
		ipa3000c01v1TxDParam OBJECT-TYPE
			SYNTAX Uint5
			MAX-ACCESS read-write
			STATUS current
			DESCRIPTION
				"D parameter (FEC mode rows)"
		::= { ipa3000c01v1Entry 175 }

		-- 1.3.6.1.4.1.10106.3.101291.1.1.177
		ipa3000c01v1TxTspkInIppk OBJECT-TYPE
			SYNTAX Uint3
			MAX-ACCESS read-write
			STATUS current
			DESCRIPTION
				"TS packets in each IP packet"
		::= { ipa3000c01v1Entry 177 }

		-- 1.3.6.1.4.1.10106.3.101291.1.1.179
		ipa3000c01v1TxRowDelay OBJECT-TYPE
			SYNTAX Uint5
			MAX-ACCESS read-write
			STATUS current
			DESCRIPTION
				"FEC row delay"
		::= { ipa3000c01v1Entry 179 }

		-- 1.3.6.1.4.1.10106.3.101291.1.1.181
		ipa3000c01v1TxColDelay OBJECT-TYPE
			SYNTAX Uint8
			MAX-ACCESS read-write
			STATUS current
			DESCRIPTION
				"FEC column delay"
		::= { ipa3000c01v1Entry 181 }

		-- 1.3.6.1.4.1.10106.3.101291.1.1.183
		ipa3000c01v1LowCost OBJECT-TYPE
			SYNTAX Bit0No1Yes
			MAX-ACCESS read-write
			STATUS current
			DESCRIPTION
				"TOS.  Low cost"
		::= { ipa3000c01v1Entry 183 }

		-- 1.3.6.1.4.1.10106.3.101291.1.1.185
		ipa3000c01v1HighReliabilty OBJECT-TYPE
			SYNTAX Bit0No1Yes
			MAX-ACCESS read-write
			STATUS current
			DESCRIPTION
				"TOS. High reliability"
		::= { ipa3000c01v1Entry 185 }

		-- 1.3.6.1.4.1.10106.3.101291.1.1.187
		ipa3000c01v1HighThroughput OBJECT-TYPE
			SYNTAX Bit0No1Yes
			MAX-ACCESS read-write
			STATUS current
			DESCRIPTION
				"TOS. High Throughput"
		::= { ipa3000c01v1Entry 187 }

		-- 1.3.6.1.4.1.10106.3.101291.1.1.189
		ipa3000c01v1LowDelay OBJECT-TYPE
			SYNTAX Bit0No1Yes
			MAX-ACCESS read-write
			STATUS current
			DESCRIPTION
				"TOS. Low delay"
		::= { ipa3000c01v1Entry 189 }

		-- 1.3.6.1.4.1.10106.3.101291.1.1.191
		ipa3000c01v1Precedence OBJECT-TYPE
			SYNTAX IpaPrecedence
			MAX-ACCESS read-write
			STATUS current
			DESCRIPTION
				"TOS. Precedence"
		::= { ipa3000c01v1Entry 191 }

		-- 1.3.6.1.4.1.10106.3.101291.1.1.193
		ipa3000c01v1Ttl OBJECT-TYPE
			SYNTAX Uint8
			MAX-ACCESS read-write
			STATUS current
			DESCRIPTION
				"Time to live"
		::= { ipa3000c01v1Entry 193 }

		-- 1.3.6.1.4.1.10106.3.101291.1.1.195
		ipa3000c01v11ppsFail OBJECT-TYPE
			SYNTAX BitFail
			MAX-ACCESS read-only
			STATUS current
			DESCRIPTION
				"1PPS reference input status"
		::= { ipa3000c01v1Entry 195 }

		-- 1.3.6.1.4.1.10106.3.101291.1.1.196
		ipa3000c01v11ppsFailTrapEnable OBJECT-TYPE
			SYNTAX AlarmEnable
			MAX-ACCESS read-write
			STATUS current
			DESCRIPTION
				"1PPS reference input status Trap Enable"
		::= { ipa3000c01v1Entry 196 }

		-- 1.3.6.1.4.1.10106.3.101291.1.1.197
		ipa3000c01v110mhzFail OBJECT-TYPE
			SYNTAX BitFail
			MAX-ACCESS read-only
			STATUS current
			DESCRIPTION
				"10MHz reference input status"
		::= { ipa3000c01v1Entry 197 }

		-- 1.3.6.1.4.1.10106.3.101291.1.1.198
		ipa3000c01v110mhzFailTrapEnable OBJECT-TYPE
			SYNTAX AlarmEnable
			MAX-ACCESS read-write
			STATUS current
			DESCRIPTION
				"10MHz reference input status Trap Enable"
		::= { ipa3000c01v1Entry 198 }

		-- 1.3.6.1.4.1.10106.3.101291.1.1.199
		ipa3000c01v1OutputFail OBJECT-TYPE
			SYNTAX BitFail
			MAX-ACCESS read-only
			STATUS current
			DESCRIPTION
				"The output signal is not valid because all inputs failed"
		::= { ipa3000c01v1Entry 199 }

		-- 1.3.6.1.4.1.10106.3.101291.1.1.200
		ipa3000c01v1OutputFailTrapEnable OBJECT-TYPE
			SYNTAX AlarmEnable
			MAX-ACCESS read-write
			STATUS current
			DESCRIPTION
				"The output signal is not valid because all inputs failed Trap Enable"
		::= { ipa3000c01v1Entry 200 }

		-- 1.3.6.1.4.1.10106.3.101291.1.1.201
		ipa3000c01v1AsiMainDelWar OBJECT-TYPE
			SYNTAX BitFail
			MAX-ACCESS read-only
			STATUS current
			DESCRIPTION
				"The ASI main delay is greater than the programmed output delay"
		::= { ipa3000c01v1Entry 201 }

		-- 1.3.6.1.4.1.10106.3.101291.1.1.202
		ipa3000c01v1AsiMainDelWarTrapEnable OBJECT-TYPE
			SYNTAX AlarmEnable
			MAX-ACCESS read-write
			STATUS current
			DESCRIPTION
				"The ASI main delay is greater than the programmed output delay Trap Enable"
		::= { ipa3000c01v1Entry 202 }

		-- 1.3.6.1.4.1.10106.3.101291.1.1.203
		ipa3000c01v1AsiResDelWar OBJECT-TYPE
			SYNTAX BitFail
			MAX-ACCESS read-only
			STATUS current
			DESCRIPTION
				"The ASI reserve delay is greater than the programmed output delay"
		::= { ipa3000c01v1Entry 203 }

		-- 1.3.6.1.4.1.10106.3.101291.1.1.204
		ipa3000c01v1AsiResDelWarTrapEnable OBJECT-TYPE
			SYNTAX AlarmEnable
			MAX-ACCESS read-write
			STATUS current
			DESCRIPTION
				"The ASI reserve delay is greater than the programmed output delay Trap Enable"
		::= { ipa3000c01v1Entry 204 }

		-- 1.3.6.1.4.1.10106.3.101291.1.1.205
		ipa3000c01v1IpMainDelWar OBJECT-TYPE
			SYNTAX BitFail
			MAX-ACCESS read-only
			STATUS current
			DESCRIPTION
				"The IP main delay is greater than the programmed output delay"
		::= { ipa3000c01v1Entry 205 }

		-- 1.3.6.1.4.1.10106.3.101291.1.1.206
		ipa3000c01v1IpMainDelWarTrapEnable OBJECT-TYPE
			SYNTAX AlarmEnable
			MAX-ACCESS read-write
			STATUS current
			DESCRIPTION
				"The IP main delay is greater than the programmed output delay Trap Enable"
		::= { ipa3000c01v1Entry 206 }

		-- 1.3.6.1.4.1.10106.3.101291.1.1.207
		ipa3000c01v1IpResDelWar OBJECT-TYPE
			SYNTAX BitFail
			MAX-ACCESS read-only
			STATUS current
			DESCRIPTION
				"The IP reserve delay is greater than the programmed output delay"
		::= { ipa3000c01v1Entry 207 }

		-- 1.3.6.1.4.1.10106.3.101291.1.1.208
		ipa3000c01v1IpResDelWarTrapEnable OBJECT-TYPE
			SYNTAX AlarmEnable
			MAX-ACCESS read-write
			STATUS current
			DESCRIPTION
				"The IP reserve delay is greater than the programmed output delay Trap Enable"
		::= { ipa3000c01v1Entry 208 }

		-- 1.3.6.1.4.1.10106.3.101291.1.1.209
		ipa3000c01v1AsiMainFail OBJECT-TYPE
			SYNTAX BitFail
			MAX-ACCESS read-only
			STATUS current
			DESCRIPTION
				"ASI main input status"
		::= { ipa3000c01v1Entry 209 }

		-- 1.3.6.1.4.1.10106.3.101291.1.1.210
		ipa3000c01v1AsiMainFailTrapEnable OBJECT-TYPE
			SYNTAX AlarmEnable
			MAX-ACCESS read-write
			STATUS current
			DESCRIPTION
				"ASI main input status Trap Enable"
		::= { ipa3000c01v1Entry 210 }

		-- 1.3.6.1.4.1.10106.3.101291.1.1.211
		ipa3000c01v1ExAsiMainFail OBJECT-TYPE
			SYNTAX BitFail
			MAX-ACCESS read-only
			STATUS current
			DESCRIPTION
				"ASI main external input fail status"
		::= { ipa3000c01v1Entry 211 }

		-- 1.3.6.1.4.1.10106.3.101291.1.1.212
		ipa3000c01v1ExAsiMainFailTrapEnable OBJECT-TYPE
			SYNTAX AlarmEnable
			MAX-ACCESS read-write
			STATUS current
			DESCRIPTION
				"ASI main external input fail status Trap Enable"
		::= { ipa3000c01v1Entry 212 }

		-- 1.3.6.1.4.1.10106.3.101291.1.1.213
		ipa3000c01v1AsiResFail OBJECT-TYPE
			SYNTAX BitFail
			MAX-ACCESS read-only
			STATUS current
			DESCRIPTION
				"ASI reserve input status"
		::= { ipa3000c01v1Entry 213 }

		-- 1.3.6.1.4.1.10106.3.101291.1.1.214
		ipa3000c01v1AsiResFailTrapEnable OBJECT-TYPE
			SYNTAX AlarmEnable
			MAX-ACCESS read-write
			STATUS current
			DESCRIPTION
				"ASI reserve input status Trap Enable"
		::= { ipa3000c01v1Entry 214 }

		-- 1.3.6.1.4.1.10106.3.101291.1.1.215
		ipa3000c01v1ExAsiResFail OBJECT-TYPE
			SYNTAX BitFail
			MAX-ACCESS read-only
			STATUS current
			DESCRIPTION
				"ASI reserve external input fail status"
		::= { ipa3000c01v1Entry 215 }

		-- 1.3.6.1.4.1.10106.3.101291.1.1.216
		ipa3000c01v1ExAsiResFailTrapEnable OBJECT-TYPE
			SYNTAX AlarmEnable
			MAX-ACCESS read-write
			STATUS current
			DESCRIPTION
				"ASI reserve external input fail status Trap Enable"
		::= { ipa3000c01v1Entry 216 }

		-- 1.3.6.1.4.1.10106.3.101291.1.1.217
		ipa3000c01v1IpMainFail OBJECT-TYPE
			SYNTAX BitFail
			MAX-ACCESS read-only
			STATUS current
			DESCRIPTION
				"IP main input status"
		::= { ipa3000c01v1Entry 217 }

		-- 1.3.6.1.4.1.10106.3.101291.1.1.218
		ipa3000c01v1IpMainFailTrapEnable OBJECT-TYPE
			SYNTAX AlarmEnable
			MAX-ACCESS read-write
			STATUS current
			DESCRIPTION
				"IP main input status Trap Enable"
		::= { ipa3000c01v1Entry 218 }

		-- 1.3.6.1.4.1.10106.3.101291.1.1.219
		ipa3000c01v1ExIpMainFail OBJECT-TYPE
			SYNTAX BitFail
			MAX-ACCESS read-only
			STATUS current
			DESCRIPTION
				"IP main external input fail status"
		::= { ipa3000c01v1Entry 219 }

		-- 1.3.6.1.4.1.10106.3.101291.1.1.220
		ipa3000c01v1ExIpMainFailTrapEnable OBJECT-TYPE
			SYNTAX AlarmEnable
			MAX-ACCESS read-write
			STATUS current
			DESCRIPTION
				"IP main external input fail status Trap Enable"
		::= { ipa3000c01v1Entry 220 }

		-- 1.3.6.1.4.1.10106.3.101291.1.1.221
		ipa3000c01v1IpResFail OBJECT-TYPE
			SYNTAX BitFail
			MAX-ACCESS read-only
			STATUS current
			DESCRIPTION
				"IP reserve input status"
		::= { ipa3000c01v1Entry 221 }

		-- 1.3.6.1.4.1.10106.3.101291.1.1.222
		ipa3000c01v1IpResFailTrapEnable OBJECT-TYPE
			SYNTAX AlarmEnable
			MAX-ACCESS read-write
			STATUS current
			DESCRIPTION
				"IP reserve input status Trap Enable"
		::= { ipa3000c01v1Entry 222 }

		-- 1.3.6.1.4.1.10106.3.101291.1.1.223
		ipa3000c01v1ExIpResFail OBJECT-TYPE
			SYNTAX BitFail
			MAX-ACCESS read-only
			STATUS current
			DESCRIPTION
				"IP reserve external input fail status"
		::= { ipa3000c01v1Entry 223 }

		-- 1.3.6.1.4.1.10106.3.101291.1.1.224
		ipa3000c01v1ExIpResFailTrapEnable OBJECT-TYPE
			SYNTAX AlarmEnable
			MAX-ACCESS read-write
			STATUS current
			DESCRIPTION
				"IP reserve external input fail status Trap Enable"
		::= { ipa3000c01v1Entry 224 }

		-- 1.3.6.1.4.1.10106.3.101291.1.1.225
		ipa3000c01v1AsimAsirSeam OBJECT-TYPE
			SYNTAX Bit0Sea1Nse
			MAX-ACCESS read-only
			STATUS current
			DESCRIPTION
				"ASI main to ASI reserve seamles switching capability"
		::= { ipa3000c01v1Entry 225 }

		-- 1.3.6.1.4.1.10106.3.101291.1.1.227
		ipa3000c01v1AsimIpmSeam OBJECT-TYPE
			SYNTAX Bit0Sea1Nse
			MAX-ACCESS read-only
			STATUS current
			DESCRIPTION
				"ASI main to IP main seamles switching capability"
		::= { ipa3000c01v1Entry 227 }

		-- 1.3.6.1.4.1.10106.3.101291.1.1.229
		ipa3000c01v1AsimIprSeam OBJECT-TYPE
			SYNTAX Bit0Sea1Nse
			MAX-ACCESS read-only
			STATUS current
			DESCRIPTION
				"ASI main to IP reserve seamles switching capability"
		::= { ipa3000c01v1Entry 229 }

		-- 1.3.6.1.4.1.10106.3.101291.1.1.231
		ipa3000c01v1AsirIpmSeam OBJECT-TYPE
			SYNTAX Bit0Sea1Nse
			MAX-ACCESS read-only
			STATUS current
			DESCRIPTION
				"ASI reserve to IP main seamles switching capability"
		::= { ipa3000c01v1Entry 231 }

		-- 1.3.6.1.4.1.10106.3.101291.1.1.233
		ipa3000c01v1AsirIprSeam OBJECT-TYPE
			SYNTAX Bit0Sea1Nse
			MAX-ACCESS read-only
			STATUS current
			DESCRIPTION
				"ASI reserve to IP reserve seamles switching capability"
		::= { ipa3000c01v1Entry 233 }

		-- 1.3.6.1.4.1.10106.3.101291.1.1.235
		ipa3000c01v1IpmIprSeam OBJECT-TYPE
			SYNTAX Bit0Sea1Nse
			MAX-ACCESS read-only
			STATUS current
			DESCRIPTION
				"IP main to IP reserve seamles switching capability"
		::= { ipa3000c01v1Entry 235 }

		-- 1.3.6.1.4.1.10106.3.101291.1.1.237
		ipa3000c01v1GlobalSeam OBJECT-TYPE
			SYNTAX Bit0Sea1Nse
			MAX-ACCESS read-only
			STATUS current
			DESCRIPTION
				"Global seamles switching capability"
		::= { ipa3000c01v1Entry 237 }

		-- 1.3.6.1.4.1.10106.3.101291.1.1.238
		ipa3000c01v1GlobalSeamTrapEnable OBJECT-TYPE
			SYNTAX AlarmEnable
			MAX-ACCESS read-write
			STATUS current
			DESCRIPTION
				"Global seamles switching capability Trap Enable"
		::= { ipa3000c01v1Entry 238 }

		-- 1.3.6.1.4.1.10106.3.101291.1.1.239
		ipa3000c01v1AsiMainDelay OBJECT-TYPE
			SYNTAX DelayX65Ms
			MAX-ACCESS read-only
			STATUS current
			DESCRIPTION
				"DVB-T mode: input delay refered to 1PPS reference"
		::= { ipa3000c01v1Entry 239 }

		-- 1.3.6.1.4.1.10106.3.101291.1.1.241
		ipa3000c01v1AsiResDelay OBJECT-TYPE
			SYNTAX DelayX65Ms
			MAX-ACCESS read-only
			STATUS current
			DESCRIPTION
				"DVB-T mode: input delay refered to 1PPS reference"
		::= { ipa3000c01v1Entry 241 }

		-- 1.3.6.1.4.1.10106.3.101291.1.1.243
		ipa3000c01v1IpMainDelay OBJECT-TYPE
			SYNTAX DelayX65Ms
			MAX-ACCESS read-only
			STATUS current
			DESCRIPTION
				"DVB-T mode: input delay refered to 1PPS reference"
		::= { ipa3000c01v1Entry 243 }

		-- 1.3.6.1.4.1.10106.3.101291.1.1.245
		ipa3000c01v1IpResDelay OBJECT-TYPE
			SYNTAX DelayX65Ms
			MAX-ACCESS read-only
			STATUS current
			DESCRIPTION
				"DVB-T mode: input delay refered to 1PPS reference"
		::= { ipa3000c01v1Entry 245 }

		-- 1.3.6.1.4.1.10106.3.101291.1.1.247
		ipa3000c01v1IpRxAddress3 OBJECT-TYPE
			SYNTAX Uint8
			MAX-ACCESS read-only
			STATUS current
			DESCRIPTION
				"RX packets source IP address (3)"
		::= { ipa3000c01v1Entry 247 }

		-- 1.3.6.1.4.1.10106.3.101291.1.1.249
		ipa3000c01v1IpRxAddress2 OBJECT-TYPE
			SYNTAX Uint8
			MAX-ACCESS read-only
			STATUS current
			DESCRIPTION
				"RX packets source IP address (2)"
		::= { ipa3000c01v1Entry 249 }

		-- 1.3.6.1.4.1.10106.3.101291.1.1.251
		ipa3000c01v1IpRxAddress1 OBJECT-TYPE
			SYNTAX Uint8
			MAX-ACCESS read-only
			STATUS current
			DESCRIPTION
				"RX packets source IP address (1)"
		::= { ipa3000c01v1Entry 251 }

		-- 1.3.6.1.4.1.10106.3.101291.1.1.253
		ipa3000c01v1IpRxAddress0 OBJECT-TYPE
			SYNTAX Uint8
			MAX-ACCESS read-only
			STATUS current
			DESCRIPTION
				"RX packets source IP address (0)"
		::= { ipa3000c01v1Entry 253 }

		-- 1.3.6.1.4.1.10106.3.101291.1.1.255
		ipa3000c01v1IpRxPort OBJECT-TYPE
			SYNTAX Uint16
			MAX-ACCESS read-only
			STATUS current
			DESCRIPTION
				"RX packets UDP source port"
		::= { ipa3000c01v1Entry 255 }

		-- 1.3.6.1.4.1.10106.3.101291.1.1.257
		ipa3000c01v1LParam OBJECT-TYPE
			SYNTAX Uint5
			MAX-ACCESS read-only
			STATUS current
			DESCRIPTION
				"L parameter (FEC mode columns)"
		::= { ipa3000c01v1Entry 257 }

		-- 1.3.6.1.4.1.10106.3.101291.1.1.259
		ipa3000c01v1FecMode OBJECT-TYPE
			SYNTAX FecMode
			MAX-ACCESS read-only
			STATUS current
			DESCRIPTION
				"Protocol"
		::= { ipa3000c01v1Entry 259 }

		-- 1.3.6.1.4.1.10106.3.101291.1.1.261
		ipa3000c01v1PacketSize OBJECT-TYPE
			SYNTAX Bit02041188
			MAX-ACCESS read-only
			STATUS current
			DESCRIPTION
				"Bytes in TS packets"
		::= { ipa3000c01v1Entry 261 }

		-- 1.3.6.1.4.1.10106.3.101291.1.1.263
		ipa3000c01v1DParam OBJECT-TYPE
			SYNTAX Uint5
			MAX-ACCESS read-only
			STATUS current
			DESCRIPTION
				"D parameter (FEC mode rows)"
		::= { ipa3000c01v1Entry 263 }

		-- 1.3.6.1.4.1.10106.3.101291.1.1.265
		ipa3000c01v1TsPckInIpPck OBJECT-TYPE
			SYNTAX Uint3
			MAX-ACCESS read-only
			STATUS current
			DESCRIPTION
				"TS packets in each IP packet"
		::= { ipa3000c01v1Entry 265 }

		-- 1.3.6.1.4.1.10106.3.101291.1.1.267
		ipa3000c01v1PacketRate OBJECT-TYPE
			SYNTAX PacketRate
			MAX-ACCESS read-only
			STATUS current
			DESCRIPTION
				"IP packet rate"
		::= { ipa3000c01v1Entry 267 }

		-- 1.3.6.1.4.1.10106.3.101291.1.1.269
		ipa3000c01v1TimeSinceReset OBJECT-TYPE
			SYNTAX TimeS4
			MAX-ACCESS read-only
			STATUS current
			DESCRIPTION
				"Elapsed time from last reset"
		::= { ipa3000c01v1Entry 269 }

		-- 1.3.6.1.4.1.10106.3.101291.1.1.271
		ipa3000c01v1LostIpPck OBJECT-TYPE
			SYNTAX Uint16
			MAX-ACCESS read-only
			STATUS current
			DESCRIPTION
				"Lost IP packets"
		::= { ipa3000c01v1Entry 271 }

		-- 1.3.6.1.4.1.10106.3.101291.1.1.273
		ipa3000c01v1RecoveredIpPck OBJECT-TYPE
			SYNTAX Uint16
			MAX-ACCESS read-only
			STATUS current
			DESCRIPTION
				"Recovered IP packets"
		::= { ipa3000c01v1Entry 273 }

		-- 1.3.6.1.4.1.10106.3.101291.1.1.275
		ipa3000c01v1OutOrdIpPck OBJECT-TYPE
			SYNTAX Uint16
			MAX-ACCESS read-only
			STATUS current
			DESCRIPTION
				"Out of order IP packets"
		::= { ipa3000c01v1Entry 275 }

		-- 1.3.6.1.4.1.10106.3.101291.1.1.277
		ipa3000c01v1FecRate OBJECT-TYPE
			SYNTAX PacketRate
			MAX-ACCESS read-only
			STATUS current
			DESCRIPTION
				"FEC packet rate"
		::= { ipa3000c01v1Entry 277 }

		-- 1.3.6.1.4.1.10106.3.101291.1.1.279
		ipa3000c01v1Link OBJECT-TYPE
			SYNTAX IpaEtherStat
			MAX-ACCESS read-only
			STATUS current
			DESCRIPTION
				"Ethernet conection status"
		::= { ipa3000c01v1Entry 279 }

		-- 1.3.6.1.4.1.10106.3.101291.1.1.281
		ipa3000c01v1DestAvailable OBJECT-TYPE
			SYNTAX Bit0No1Yes
			MAX-ACCESS read-only
			STATUS current
			DESCRIPTION
				"Destination IP available"
		::= { ipa3000c01v1Entry 281 }

		-- 1.3.6.1.4.1.10106.3.101291.1.1.283
		ipa3000c01v1BufferStatus OBJECT-TYPE
			SYNTAX Rate1
			MAX-ACCESS read-only
			STATUS current
			DESCRIPTION
				"Buffer filling status in non DVB-T mode"
		::= { ipa3000c01v1Entry 283 }

		-- 1.3.6.1.4.1.10106.3.101291.1.1.285
		ipa3000c01v1PingStatus OBJECT-TYPE
			SYNTAX IpaPingStat
			MAX-ACCESS read-only
			STATUS current
			DESCRIPTION
				"Ping status"
		::= { ipa3000c01v1Entry 285 }

		-- 1.3.6.1.4.1.10106.3.101291.1.1.287
		ipa3000c01v1SerialNo OBJECT-TYPE
			SYNTAX SerialNo
			MAX-ACCESS read-only
			STATUS current
			DESCRIPTION
				"Serial number"
		::= { ipa3000c01v1Entry 287 }

		-- 1.3.6.1.4.1.10106.3.101291.1.1.289
		ipa3000c01v1NullPckRtp OBJECT-TYPE
			SYNTAX Bit0No1Yes
			MAX-ACCESS read-write
			STATUS current
			DESCRIPTION
				"Selects if NULL packets are inserted if there are unrecovered packets when using RTP protocol"
		::= { ipa3000c01v1Entry 289 }

		-- 1.3.6.1.4.1.10106.3.101291.1.1.291
		ipa3000c01v1Str1IgmFAdd3 OBJECT-TYPE
			SYNTAX Uint8
			MAX-ACCESS read-write
			STATUS current
			DESCRIPTION
				"Source IP address (3)"
		::= { ipa3000c01v1Entry 291 }

		-- 1.3.6.1.4.1.10106.3.101291.1.1.293
		ipa3000c01v1Str1IgmFAdd2 OBJECT-TYPE
			SYNTAX Uint8
			MAX-ACCESS read-write
			STATUS current
			DESCRIPTION
				"Source IP address (2)"
		::= { ipa3000c01v1Entry 293 }

		-- 1.3.6.1.4.1.10106.3.101291.1.1.295
		ipa3000c01v1Str1IgmFAdd1 OBJECT-TYPE
			SYNTAX Uint8
			MAX-ACCESS read-write
			STATUS current
			DESCRIPTION
				"Source IP address (1)"
		::= { ipa3000c01v1Entry 295 }

		-- 1.3.6.1.4.1.10106.3.101291.1.1.297
		ipa3000c01v1Str1IgmFAdd0 OBJECT-TYPE
			SYNTAX Uint8
			MAX-ACCESS read-write
			STATUS current
			DESCRIPTION
				"Source IP address (0)"
		::= { ipa3000c01v1Entry 297 }

		-- 1.3.6.1.4.1.10106.3.101291.1.1.299
		ipa3000c01v1Str2IgmFAdd3 OBJECT-TYPE
			SYNTAX Uint8
			MAX-ACCESS read-write
			STATUS current
			DESCRIPTION
				"Source IP address (3)"
		::= { ipa3000c01v1Entry 299 }

		-- 1.3.6.1.4.1.10106.3.101291.1.1.301
		ipa3000c01v1Str2IgmFAdd2 OBJECT-TYPE
			SYNTAX Uint8
			MAX-ACCESS read-write
			STATUS current
			DESCRIPTION
				"Source IP address (2)"
		::= { ipa3000c01v1Entry 301 }

		-- 1.3.6.1.4.1.10106.3.101291.1.1.303
		ipa3000c01v1Str2IgmFAdd1 OBJECT-TYPE
			SYNTAX Uint8
			MAX-ACCESS read-write
			STATUS current
			DESCRIPTION
				"Source IP address (1)"
		::= { ipa3000c01v1Entry 303 }

		-- 1.3.6.1.4.1.10106.3.101291.1.1.305
		ipa3000c01v1Str2IgmFAdd0 OBJECT-TYPE
			SYNTAX Uint8
			MAX-ACCESS read-write
			STATUS current
			DESCRIPTION
				"Source IP address (0)"
		::= { ipa3000c01v1Entry 305 }

		-- 1.3.6.1.4.1.10106.3.101291.1.1.307
		ipa3000c01v1EnSeamNondvbt OBJECT-TYPE
			SYNTAX Bit0No1Yes
			MAX-ACCESS read-write
			STATUS current
			DESCRIPTION
				"Allows enabling seamless mode with non DVB-T signals"
		::= { ipa3000c01v1Entry 307 }

		-- 1.3.6.1.4.1.10106.3.101291.1.1.309
		ipa3000c01v1IpLinkFailEn OBJECT-TYPE
			SYNTAX Bit0No1Yes
			MAX-ACCESS read-write
			STATUS current
			DESCRIPTION
				"IP link lose signals fail in F_OUT GPO"
		::= { ipa3000c01v1Entry 309 }

		-- 1.3.6.1.4.1.10106.3.101291.1.1.311
		ipa3000c01v1IpDestFailEn OBJECT-TYPE
			SYNTAX Bit0No1Yes
			MAX-ACCESS read-write
			STATUS current
			DESCRIPTION
				"IP destination absence signals fail in F_OUT GPO"
		::= { ipa3000c01v1Entry 311 }

		-- 1.3.6.1.4.1.10106.3.101291.1.1.313
		ipa3000c01v1System OBJECT-TYPE
			SYNTAX IpaEtherSys
			MAX-ACCESS read-only
			STATUS current
			DESCRIPTION
				"Ethernet conection system"
		::= { ipa3000c01v1Entry 313 }

		-- 1.3.6.1.4.1.10106.3.101291.1.1.315
		ipa3000c01v1SpeedForce OBJECT-TYPE
			SYNTAX Bit0Ann1For
			MAX-ACCESS read-write
			STATUS current
			DESCRIPTION
				"Allows selecting if the speed/mode is forced or announced for autonegotiation"
		::= { ipa3000c01v1Entry 315 }

		-- 1.3.6.1.4.1.10106.3.101291.1.1.317
		ipa3000c01v1BadCrcPck OBJECT-TYPE
			SYNTAX Uint16
			MAX-ACCESS read-only
			STATUS current
			DESCRIPTION
				"Bad CRC packets"
		::= { ipa3000c01v1Entry 317 }

		-- 1.3.6.1.4.1.10106.3.101291.1.1.319
		ipa3000c01v1InpFailMode OBJECT-TYPE
			SYNTAX Bit0Yes1No
			MAX-ACCESS read-write
			STATUS current
			DESCRIPTION
				"Selects if the output is muted when all the inputs fail"
		::= { ipa3000c01v1Entry 319 }

		-- 1.3.6.1.4.1.10106.3.101291.1.1.321
		ipa3000c01v1MaxDelayTxIp OBJECT-TYPE
			SYNTAX TimeX10Ms
			MAX-ACCESS read-write
			STATUS current
			DESCRIPTION
				"Time before starting to transmit after recovering signal"
		::= { ipa3000c01v1Entry 321 }

		-- 1.3.6.1.4.1.10106.3.362002
		ipa3000c01v2 OBJECT IDENTIFIER ::= { albalaProducts 362002 }

		-- 1.3.6.1.4.1.10106.3.362002.1
		ipa3000c01v2Table  OBJECT-TYPE
			SYNTAX SEQUENCE OF Ipa3000c01v2Entry
			MAX-ACCESS not-accessible
			STATUS current
			DESCRIPTION
				"Module  IPA3000C01V2 Table"
			::= { ipa3000c01v2 1 }

		-- 1.3.6.1.4.1.10106.3.362002.1.1
		ipa3000c01v2Entry  OBJECT-TYPE
			SYNTAX Ipa3000c01v2Entry
			MAX-ACCESS not-accessible
			STATUS current
			DESCRIPTION
				"Module IPA3000C01V2 Entry"
			INDEX { ipa3000c01v2Index }
			::= { ipa3000c01v2Table 1 }

			Ipa3000c01v2Entry ::=
			SEQUENCE {
				ipa3000c01v2Index
				ModuleIndex,
				ipa3000c01v2Mode
				ChgOverMode2,
				ipa3000c01v2ModeTrapEnable
				AlarmEnable,
				ipa3000c01v2DvbTMode
				Bit0No1Yes,
				ipa3000c01v2DvbTModeTrapEnable
				AlarmEnable,
				ipa3000c01v2NullPckRtp
				Bit0No1Yes,
				ipa3000c01v2NarrowPllBw
				Bit0No1Yes,
				ipa3000c01v2Buzzer
				BitMask,
				ipa3000c01v2SeamlessPrior
				Bit0No1Yes,
				ipa3000c01v2EnSeamNondvbt
				Bit0No1Yes,
				ipa3000c01v2Input
				ChgOverInput3,
				ipa3000c01v2InputTrapEnable
				AlarmEnable,
				ipa3000c01v2InputStChange
				Bit0No1Yes,
				ipa3000c01v2InputChange
				Bit0No1Yes,
				ipa3000c01v2EnaAsiMain
				BitMask,
				ipa3000c01v2EnaAsiRes
				BitMask,
				ipa3000c01v2EnaIpMain
				BitMask,
				ipa3000c01v2EnaIpRes
				BitMask,
				ipa3000c01v2OutDelay
				DelayX100Ns,
				ipa3000c01v2OutDelayTrapEnable
				AlarmEnable,
				ipa3000c01v2AsiMainPrior
				Uint2,
				ipa3000c01v2AsiResPrior
				Uint2,
				ipa3000c01v2IpMainPrior
				Uint2,
				ipa3000c01v2IpResPrior
				Uint2,
				ipa3000c01v2StatReset
				Bit0No1Yes,
				ipa3000c01v2StatSel
				Bit0Ipm1Ipr,
				ipa3000c01v2StatMode
				Bit01s1Total,
				ipa3000c01v2IgmpVersion
				Bit0V21V3,
				ipa3000c01v2EthMode
				EthMode,
				ipa3000c01v2PingEnable
				Bit0No1Yes,
				ipa3000c01v2PacketDelay
				DelayPacket1,
				ipa3000c01v2IpLinkFailEn
				Bit0No1Yes,
				ipa3000c01v2IpDestFailEn
				Bit0No1Yes,
				ipa3000c01v2SpeedForce
				Bit0Ann1For,
				ipa3000c01v2Str1UipDAdd3
				Uint8,
				ipa3000c01v2Str1UipDAdd2
				Uint8,
				ipa3000c01v2Str1UipDAdd1
				Uint8,
				ipa3000c01v2Str1UipDAdd0
				Uint8,
				ipa3000c01v2Str1MipDAdd3
				Uint8,
				ipa3000c01v2Str1MipDAdd2
				Uint8,
				ipa3000c01v2Str1MipDAdd1
				Uint8,
				ipa3000c01v2Str1MipDAdd0
				Uint8,
				ipa3000c01v2Str1DPortMsb
				Uint8,
				ipa3000c01v2Str1DPortLsb
				Uint8,
				ipa3000c01v2Str1FecEna
				Bit0No1Yes,
				ipa3000c01v2Str1MulticEna
				IpaTxMode,
				ipa3000c01v2VlanRx1Enable
				Bit0No1Yes,
				ipa3000c01v2VlanRx1Reg1
				Uint8,
				ipa3000c01v2VlanRx1Reg2
				Uint8,
				ipa3000c01v2Str2UipDAdd3
				Uint8,
				ipa3000c01v2Str2UipDAdd2
				Uint8,
				ipa3000c01v2Str2UipDAdd1
				Uint8,
				ipa3000c01v2Str2UipDAdd0
				Uint8,
				ipa3000c01v2Str2MipDAdd3
				Uint8,
				ipa3000c01v2Str2MipDAdd2
				Uint8,
				ipa3000c01v2Str2MipDAdd1
				Uint8,
				ipa3000c01v2Str2MipDAdd0
				Uint8,
				ipa3000c01v2Str2DPortMsb
				Uint8,
				ipa3000c01v2Str2DPortLsb
				Uint8,
				ipa3000c01v2Str2FecEna
				Bit0No1Yes,
				ipa3000c01v2Str2MulticEna
				IpaTxMode,
				ipa3000c01v2VlanRx2Enable
				Bit0No1Yes,
				ipa3000c01v2VlanRx2Reg1
				Uint8,
				ipa3000c01v2VlanRx2Reg2
				Uint8,
				ipa3000c01v2TxUniEna
				Bit0No1Yes,
				ipa3000c01v2TxMultiEna
				IpaTxMode,
				ipa3000c01v2LocalIpAdd3
				Uint8,
				ipa3000c01v2LocalIpAdd2
				Uint8,
				ipa3000c01v2LocalIpAdd1
				Uint8,
				ipa3000c01v2LocalIpAdd0
				Uint8,
				ipa3000c01v2LocalIpMask3
				Uint8,
				ipa3000c01v2LocalIpMask2
				Uint8,
				ipa3000c01v2LocalIpMask1
				Uint8,
				ipa3000c01v2LocalIpMask0
				Uint8,
				ipa3000c01v2LocalIpGway3
				Uint8,
				ipa3000c01v2LocalIpGway2
				Uint8,
				ipa3000c01v2LocalIpGway1
				Uint8,
				ipa3000c01v2LocalIpGway0
				Uint8,
				ipa3000c01v2TxUipAdd3
				Uint8,
				ipa3000c01v2TxUipAdd2
				Uint8,
				ipa3000c01v2TxUipAdd1
				Uint8,
				ipa3000c01v2TxUipAdd0
				Uint8,
				ipa3000c01v2TxMipAdd3
				Uint8,
				ipa3000c01v2TxMipAdd2
				Uint8,
				ipa3000c01v2TxMipAdd1
				Uint8,
				ipa3000c01v2TxMipAdd0
				Uint8,
				ipa3000c01v2TxSPortMsb
				Uint8,
				ipa3000c01v2TxSPortLsb
				Uint8,
				ipa3000c01v2TxDPortMsb
				Uint8,
				ipa3000c01v2TxDPortLsb
				Uint8,
				ipa3000c01v2VlanTxEnable
				Bit0No1Yes,
				ipa3000c01v2VlanTxPriority
				Uint3,
				ipa3000c01v2VlanTxReg1
				Uint8,
				ipa3000c01v2VlanTxReg2
				Uint8,
				ipa3000c01v2TxLParam
				Uint5,
				ipa3000c01v2TxFecMode
				FecMode,
				ipa3000c01v2TxDParam
				Uint5,
				ipa3000c01v2TxTspkInIppk
				Uint3,
				ipa3000c01v2TxRowDelay
				Uint5,
				ipa3000c01v2TxColDelay
				Uint8,
				ipa3000c01v2LowCost
				Bit0No1Yes,
				ipa3000c01v2HighReliabilty
				Bit0No1Yes,
				ipa3000c01v2HighThroughput
				Bit0No1Yes,
				ipa3000c01v2LowDelay
				Bit0No1Yes,
				ipa3000c01v2Precedence
				IpaPrecedence,
				ipa3000c01v2Ttl
				Uint8,
				ipa3000c01v2Str1IgmFAdd3
				Uint8,
				ipa3000c01v2Str1IgmFAdd2
				Uint8,
				ipa3000c01v2Str1IgmFAdd1
				Uint8,
				ipa3000c01v2Str1IgmFAdd0
				Uint8,
				ipa3000c01v2Str2IgmFAdd3
				Uint8,
				ipa3000c01v2Str2IgmFAdd2
				Uint8,
				ipa3000c01v2Str2IgmFAdd1
				Uint8,
				ipa3000c01v2Str2IgmFAdd0
				Uint8,
				ipa3000c01v21ppsFail
				BitFail,
				ipa3000c01v21ppsFailTrapEnable
				AlarmEnable,
				ipa3000c01v210mhzFail
				BitFail,
				ipa3000c01v210mhzFailTrapEnable
				AlarmEnable,
				ipa3000c01v2OutputFail
				BitFail,
				ipa3000c01v2OutputFailTrapEnable
				AlarmEnable,
				ipa3000c01v2AsiMainDelWar
				BitFail,
				ipa3000c01v2AsiMainDelWarTrapEnable
				AlarmEnable,
				ipa3000c01v2AsiResDelWar
				BitFail,
				ipa3000c01v2AsiResDelWarTrapEnable
				AlarmEnable,
				ipa3000c01v2IpMainDelWar
				BitFail,
				ipa3000c01v2IpMainDelWarTrapEnable
				AlarmEnable,
				ipa3000c01v2IpResDelWar
				BitFail,
				ipa3000c01v2IpResDelWarTrapEnable
				AlarmEnable,
				ipa3000c01v2AsiMainFail
				BitFail,
				ipa3000c01v2AsiMainFailTrapEnable
				AlarmEnable,
				ipa3000c01v2ExAsiMainFail
				BitFail,
				ipa3000c01v2ExAsiMainFailTrapEnable
				AlarmEnable,
				ipa3000c01v2AsiResFail
				BitFail,
				ipa3000c01v2AsiResFailTrapEnable
				AlarmEnable,
				ipa3000c01v2ExAsiResFail
				BitFail,
				ipa3000c01v2ExAsiResFailTrapEnable
				AlarmEnable,
				ipa3000c01v2IpMainFail
				BitFail,
				ipa3000c01v2IpMainFailTrapEnable
				AlarmEnable,
				ipa3000c01v2ExIpMainFail
				BitFail,
				ipa3000c01v2ExIpMainFailTrapEnable
				AlarmEnable,
				ipa3000c01v2IpResFail
				BitFail,
				ipa3000c01v2IpResFailTrapEnable
				AlarmEnable,
				ipa3000c01v2ExIpResFail
				BitFail,
				ipa3000c01v2ExIpResFailTrapEnable
				AlarmEnable,
				ipa3000c01v2AsimAsirSeam
				Bit0Sea1Nse,
				ipa3000c01v2AsimIpmSeam
				Bit0Sea1Nse,
				ipa3000c01v2AsimIprSeam
				Bit0Sea1Nse,
				ipa3000c01v2AsirIpmSeam
				Bit0Sea1Nse,
				ipa3000c01v2AsirIprSeam
				Bit0Sea1Nse,
				ipa3000c01v2IpmIprSeam
				Bit0Sea1Nse,
				ipa3000c01v2GlobalSeam
				Bit0Sea1Nse,
				ipa3000c01v2GlobalSeamTrapEnable
				AlarmEnable,
				ipa3000c01v2AsiMainDelay
				DelayX65Ms,
				ipa3000c01v2AsiResDelay
				DelayX65Ms,
				ipa3000c01v2IpMainDelay
				DelayX65Ms,
				ipa3000c01v2IpResDelay
				DelayX65Ms,
				ipa3000c01v2IpRxAddress3
				Uint8,
				ipa3000c01v2IpRxAddress2
				Uint8,
				ipa3000c01v2IpRxAddress1
				Uint8,
				ipa3000c01v2IpRxAddress0
				Uint8,
				ipa3000c01v2IpRxPort
				Uint16,
				ipa3000c01v2LParam
				Uint5,
				ipa3000c01v2FecMode
				FecMode,
				ipa3000c01v2PacketSize
				Bit02041188,
				ipa3000c01v2DParam
				Uint5,
				ipa3000c01v2TsPckInIpPck
				Uint3,
				ipa3000c01v2PacketRate
				PacketRate,
				ipa3000c01v2TimeSinceReset
				TimeS4,
				ipa3000c01v2LostIpPck
				Uint16,
				ipa3000c01v2RecoveredIpPck
				Uint16,
				ipa3000c01v2BadCrcPck
				Uint16,
				ipa3000c01v2OutOrdIpPck
				Uint16,
				ipa3000c01v2FecRate
				PacketRate,
				ipa3000c01v2Link
				IpaEtherStat,
				ipa3000c01v2System
				IpaEtherSys,
				ipa3000c01v2DestAvailable
				Bit0No1Yes,
				ipa3000c01v2BufferStatus
				Rate1,
				ipa3000c01v2PingStatus
				IpaPingStat,
				ipa3000c01v2SerialNo
				SerialNo,
				ipa3000c01v2InpFailMode
				Bit0Yes1No,
				ipa3000c01v2MaxDelayTxIp
				TimeX10Ms
			 }

		-- 1.3.6.1.4.1.10106.3.101291.1.1.1
		ipa3000c01v2Index OBJECT-TYPE
			SYNTAX ModuleIndex
			MAX-ACCESS read-only
			STATUS current
			DESCRIPTION
				"Index of IPA3000C01V2 Table"
		::= { ipa3000c01v2Entry 1 }

		-- 1.3.6.1.4.1.10106.3.101291.1.1.3
		ipa3000c01v2Mode OBJECT-TYPE
			SYNTAX ChgOverMode2
			MAX-ACCESS read-write
			STATUS current
			DESCRIPTION
				"Allows selecting the switching mode"
		::= { ipa3000c01v2Entry 3 }

		-- 1.3.6.1.4.1.10106.3.101291.1.1.4
		ipa3000c01v2ModeTrapEnable OBJECT-TYPE
			SYNTAX AlarmEnable
			MAX-ACCESS read-write
			STATUS current
			DESCRIPTION
				"Allows selecting the switching mode Trap Enable"
		::= { ipa3000c01v2Entry 4 }

		-- 1.3.6.1.4.1.10106.3.101291.1.1.5
		ipa3000c01v2DvbTMode OBJECT-TYPE
			SYNTAX Bit0No1Yes
			MAX-ACCESS read-write
			STATUS current
			DESCRIPTION
				"Selects DVB-T mode."
		::= { ipa3000c01v2Entry 5 }

		-- 1.3.6.1.4.1.10106.3.101291.1.1.6
		ipa3000c01v2DvbTModeTrapEnable OBJECT-TYPE
			SYNTAX AlarmEnable
			MAX-ACCESS read-write
			STATUS current
			DESCRIPTION
				"Selects DVB-T mode. Trap Enable"
		::= { ipa3000c01v2Entry 6 }

		-- 1.3.6.1.4.1.10106.3.101291.1.1.7
		ipa3000c01v2NullPckRtp OBJECT-TYPE
			SYNTAX Bit0No1Yes
			MAX-ACCESS read-write
			STATUS current
			DESCRIPTION
				"Selects if NULL packets are inserted if there are unrecovered packets when using RTP protocol"
		::= { ipa3000c01v2Entry 7 }

		-- 1.3.6.1.4.1.10106.3.101291.1.1.9
		ipa3000c01v2NarrowPllBw OBJECT-TYPE
			SYNTAX Bit0No1Yes
			MAX-ACCESS read-write
			STATUS current
			DESCRIPTION
				"Allows selecting a narrow PLL bandwidth in the clock packet PLL in non DVB-T mode to achieve a very stable bitrate"
		::= { ipa3000c01v2Entry 9 }

		-- 1.3.6.1.4.1.10106.3.101291.1.1.11
		ipa3000c01v2Buzzer OBJECT-TYPE
			SYNTAX BitMask
			MAX-ACCESS read-write
			STATUS current
			DESCRIPTION
				"Allows buzzer operation"
		::= { ipa3000c01v2Entry 11 }

		-- 1.3.6.1.4.1.10106.3.101291.1.1.13
		ipa3000c01v2SeamlessPrior OBJECT-TYPE
			SYNTAX Bit0No1Yes
			MAX-ACCESS read-write
			STATUS current
			DESCRIPTION
				"Selects if seamless status has priority over input priority in hafl-auto mode"
		::= { ipa3000c01v2Entry 13 }

		-- 1.3.6.1.4.1.10106.3.101291.1.1.15
		ipa3000c01v2EnSeamNondvbt OBJECT-TYPE
			SYNTAX Bit0No1Yes
			MAX-ACCESS read-write
			STATUS current
			DESCRIPTION
				"Allows enabling seamless mode with non DVB-T signals"
		::= { ipa3000c01v2Entry 15 }

		-- 1.3.6.1.4.1.10106.3.101291.1.1.17
		ipa3000c01v2Input OBJECT-TYPE
			SYNTAX ChgOverInput3
			MAX-ACCESS read-write
			STATUS current
			DESCRIPTION
				"Selected input"
		::= { ipa3000c01v2Entry 17 }

		-- 1.3.6.1.4.1.10106.3.101291.1.1.18
		ipa3000c01v2InputTrapEnable OBJECT-TYPE
			SYNTAX AlarmEnable
			MAX-ACCESS read-write
			STATUS current
			DESCRIPTION
				"Selected input Trap Enable"
		::= { ipa3000c01v2Entry 18 }

		-- 1.3.6.1.4.1.10106.3.101291.1.1.19
		ipa3000c01v2InputStChange OBJECT-TYPE
			SYNTAX Bit0No1Yes
			MAX-ACCESS read-write
			STATUS current
			DESCRIPTION
				"Signals a change in fail status"
		::= { ipa3000c01v2Entry 19 }

		-- 1.3.6.1.4.1.10106.3.101291.1.1.21
		ipa3000c01v2InputChange OBJECT-TYPE
			SYNTAX Bit0No1Yes
			MAX-ACCESS read-write
			STATUS current
			DESCRIPTION
				"Signals a change in selected input"
		::= { ipa3000c01v2Entry 21 }

		-- 1.3.6.1.4.1.10106.3.101291.1.1.23
		ipa3000c01v2EnaAsiMain OBJECT-TYPE
			SYNTAX BitMask
			MAX-ACCESS read-write
			STATUS current
			DESCRIPTION
				"Allows disabling ASI main input when it is not used"
		::= { ipa3000c01v2Entry 23 }

		-- 1.3.6.1.4.1.10106.3.101291.1.1.25
		ipa3000c01v2EnaAsiRes OBJECT-TYPE
			SYNTAX BitMask
			MAX-ACCESS read-write
			STATUS current
			DESCRIPTION
				"Allows disabling ASI reserve input when it is not used"
		::= { ipa3000c01v2Entry 25 }

		-- 1.3.6.1.4.1.10106.3.101291.1.1.27
		ipa3000c01v2EnaIpMain OBJECT-TYPE
			SYNTAX BitMask
			MAX-ACCESS read-write
			STATUS current
			DESCRIPTION
				"Allows disabling IP main input when it is not used"
		::= { ipa3000c01v2Entry 27 }

		-- 1.3.6.1.4.1.10106.3.101291.1.1.29
		ipa3000c01v2EnaIpRes OBJECT-TYPE
			SYNTAX BitMask
			MAX-ACCESS read-write
			STATUS current
			DESCRIPTION
				"Allows disabling IP reserver input when it is not used"
		::= { ipa3000c01v2Entry 29 }

		-- 1.3.6.1.4.1.10106.3.101291.1.1.31
		ipa3000c01v2OutDelay OBJECT-TYPE
			SYNTAX DelayX100Ns
			MAX-ACCESS read-write
			STATUS current
			DESCRIPTION
				"Output delay refered to 1PPS reference in DVB-T mode"
		::= { ipa3000c01v2Entry 31 }

		-- 1.3.6.1.4.1.10106.3.101291.1.1.32
		ipa3000c01v2OutDelayTrapEnable OBJECT-TYPE
			SYNTAX AlarmEnable
			MAX-ACCESS read-write
			STATUS current
			DESCRIPTION
				"Output delay refered to 1PPS reference in DVB-T mode Trap Enable"
		::= { ipa3000c01v2Entry 32 }

		-- 1.3.6.1.4.1.10106.3.101291.1.1.33
		ipa3000c01v2AsiMainPrior OBJECT-TYPE
			SYNTAX Uint2
			MAX-ACCESS read-write
			STATUS current
			DESCRIPTION
				"Allows selecting the ASI main input priority"
		::= { ipa3000c01v2Entry 33 }

		-- 1.3.6.1.4.1.10106.3.101291.1.1.35
		ipa3000c01v2AsiResPrior OBJECT-TYPE
			SYNTAX Uint2
			MAX-ACCESS read-write
			STATUS current
			DESCRIPTION
				"Allows selecting the ASI reserve input priority"
		::= { ipa3000c01v2Entry 35 }

		-- 1.3.6.1.4.1.10106.3.101291.1.1.37
		ipa3000c01v2IpMainPrior OBJECT-TYPE
			SYNTAX Uint2
			MAX-ACCESS read-write
			STATUS current
			DESCRIPTION
				"Allows selecting the IP main input priority"
		::= { ipa3000c01v2Entry 37 }

		-- 1.3.6.1.4.1.10106.3.101291.1.1.39
		ipa3000c01v2IpResPrior OBJECT-TYPE
			SYNTAX Uint2
			MAX-ACCESS read-write
			STATUS current
			DESCRIPTION
				"Allows selecting the IP reserve input priority"
		::= { ipa3000c01v2Entry 39 }

		-- 1.3.6.1.4.1.10106.3.101291.1.1.41
		ipa3000c01v2StatReset OBJECT-TYPE
			SYNTAX Bit0No1Yes
			MAX-ACCESS read-write
			STATUS current
			DESCRIPTION
				"Allows reseting the statistics measurements"
		::= { ipa3000c01v2Entry 41 }

		-- 1.3.6.1.4.1.10106.3.101291.1.1.43
		ipa3000c01v2StatSel OBJECT-TYPE
			SYNTAX Bit0Ipm1Ipr
			MAX-ACCESS read-write
			STATUS current
			DESCRIPTION
				"Allows selecting the channel to be displayed"
		::= { ipa3000c01v2Entry 43 }

		-- 1.3.6.1.4.1.10106.3.101291.1.1.45
		ipa3000c01v2StatMode OBJECT-TYPE
			SYNTAX Bit01s1Total
			MAX-ACCESS read-write
			STATUS current
			DESCRIPTION
				"Allows selecting the statistics mode"
		::= { ipa3000c01v2Entry 45 }

		-- 1.3.6.1.4.1.10106.3.101291.1.1.47
		ipa3000c01v2IgmpVersion OBJECT-TYPE
			SYNTAX Bit0V21V3
			MAX-ACCESS read-write
			STATUS current
			DESCRIPTION
				"Allows selecting the IGMP version"
		::= { ipa3000c01v2Entry 47 }

		-- 1.3.6.1.4.1.10106.3.101291.1.1.49
		ipa3000c01v2EthMode OBJECT-TYPE
			SYNTAX EthMode
			MAX-ACCESS read-write
			STATUS current
			DESCRIPTION
				"Allows selecting the Ethernet operating mode"
		::= { ipa3000c01v2Entry 49 }

		-- 1.3.6.1.4.1.10106.3.101291.1.1.51
		ipa3000c01v2PingEnable OBJECT-TYPE
			SYNTAX Bit0No1Yes
			MAX-ACCESS read-write
			STATUS current
			DESCRIPTION
				"Allows making a periodic ping to the unicast address"
		::= { ipa3000c01v2Entry 51 }

		-- 1.3.6.1.4.1.10106.3.101291.1.1.53
		ipa3000c01v2PacketDelay OBJECT-TYPE
			SYNTAX DelayPacket1
			MAX-ACCESS read-write
			STATUS current
			DESCRIPTION
				"Output delay in TS packets in non DVB-T mode"
		::= { ipa3000c01v2Entry 53 }

		-- 1.3.6.1.4.1.10106.3.101291.1.1.55
		ipa3000c01v2IpLinkFailEn OBJECT-TYPE
			SYNTAX Bit0No1Yes
			MAX-ACCESS read-write
			STATUS current
			DESCRIPTION
				"IP link lose signals fail in F_OUT GPO"
		::= { ipa3000c01v2Entry 55 }

		-- 1.3.6.1.4.1.10106.3.101291.1.1.57
		ipa3000c01v2IpDestFailEn OBJECT-TYPE
			SYNTAX Bit0No1Yes
			MAX-ACCESS read-write
			STATUS current
			DESCRIPTION
				"IP destination absence signals fail in F_OUT GPO"
		::= { ipa3000c01v2Entry 57 }

		-- 1.3.6.1.4.1.10106.3.101291.1.1.59
		ipa3000c01v2SpeedForce OBJECT-TYPE
			SYNTAX Bit0Ann1For
			MAX-ACCESS read-write
			STATUS current
			DESCRIPTION
				"Allows selecting if the speed/mode is forced or announced for autonegotiation"
		::= { ipa3000c01v2Entry 59 }

		-- 1.3.6.1.4.1.10106.3.101291.1.1.61
		ipa3000c01v2Str1UipDAdd3 OBJECT-TYPE
			SYNTAX Uint8
			MAX-ACCESS read-write
			STATUS current
			DESCRIPTION
				"Unicast IP address (3)"
		::= { ipa3000c01v2Entry 61 }

		-- 1.3.6.1.4.1.10106.3.101291.1.1.63
		ipa3000c01v2Str1UipDAdd2 OBJECT-TYPE
			SYNTAX Uint8
			MAX-ACCESS read-write
			STATUS current
			DESCRIPTION
				"Unicast IP address (2)"
		::= { ipa3000c01v2Entry 63 }

		-- 1.3.6.1.4.1.10106.3.101291.1.1.65
		ipa3000c01v2Str1UipDAdd1 OBJECT-TYPE
			SYNTAX Uint8
			MAX-ACCESS read-write
			STATUS current
			DESCRIPTION
				"Unicast IP address (1)"
		::= { ipa3000c01v2Entry 65 }

		-- 1.3.6.1.4.1.10106.3.101291.1.1.67
		ipa3000c01v2Str1UipDAdd0 OBJECT-TYPE
			SYNTAX Uint8
			MAX-ACCESS read-write
			STATUS current
			DESCRIPTION
				"Unicast IP address (0)"
		::= { ipa3000c01v2Entry 67 }

		-- 1.3.6.1.4.1.10106.3.101291.1.1.69
		ipa3000c01v2Str1MipDAdd3 OBJECT-TYPE
			SYNTAX Uint8
			MAX-ACCESS read-write
			STATUS current
			DESCRIPTION
				"Multicast IP address (3)"
		::= { ipa3000c01v2Entry 69 }

		-- 1.3.6.1.4.1.10106.3.101291.1.1.71
		ipa3000c01v2Str1MipDAdd2 OBJECT-TYPE
			SYNTAX Uint8
			MAX-ACCESS read-write
			STATUS current
			DESCRIPTION
				"Multicast IP address (2)"
		::= { ipa3000c01v2Entry 71 }

		-- 1.3.6.1.4.1.10106.3.101291.1.1.73
		ipa3000c01v2Str1MipDAdd1 OBJECT-TYPE
			SYNTAX Uint8
			MAX-ACCESS read-write
			STATUS current
			DESCRIPTION
				"Multicast IP address (1)"
		::= { ipa3000c01v2Entry 73 }

		-- 1.3.6.1.4.1.10106.3.101291.1.1.75
		ipa3000c01v2Str1MipDAdd0 OBJECT-TYPE
			SYNTAX Uint8
			MAX-ACCESS read-write
			STATUS current
			DESCRIPTION
				"Multicast IP address (0)"
		::= { ipa3000c01v2Entry 75 }

		-- 1.3.6.1.4.1.10106.3.101291.1.1.77
		ipa3000c01v2Str1DPortMsb OBJECT-TYPE
			SYNTAX Uint8
			MAX-ACCESS read-write
			STATUS current
			DESCRIPTION
				"Destination port (msb)"
		::= { ipa3000c01v2Entry 77 }

		-- 1.3.6.1.4.1.10106.3.101291.1.1.79
		ipa3000c01v2Str1DPortLsb OBJECT-TYPE
			SYNTAX Uint8
			MAX-ACCESS read-write
			STATUS current
			DESCRIPTION
				"Destination port (lsb)"
		::= { ipa3000c01v2Entry 79 }

		-- 1.3.6.1.4.1.10106.3.101291.1.1.81
		ipa3000c01v2Str1FecEna OBJECT-TYPE
			SYNTAX Bit0No1Yes
			MAX-ACCESS read-write
			STATUS current
			DESCRIPTION
				"Enable FEC"
		::= { ipa3000c01v2Entry 81 }

		-- 1.3.6.1.4.1.10106.3.101291.1.1.83
		ipa3000c01v2Str1MulticEna OBJECT-TYPE
			SYNTAX IpaTxMode
			MAX-ACCESS read-write
			STATUS current
			DESCRIPTION
				"RX mode"
		::= { ipa3000c01v2Entry 83 }

		-- 1.3.6.1.4.1.10106.3.101291.1.1.85
		ipa3000c01v2VlanRx1Enable OBJECT-TYPE
			SYNTAX Bit0No1Yes
			MAX-ACCESS read-write
			STATUS current
			DESCRIPTION
				"VLAN Enable"
		::= { ipa3000c01v2Entry 85 }

		-- 1.3.6.1.4.1.10106.3.101291.1.1.87
		ipa3000c01v2VlanRx1Reg1 OBJECT-TYPE
			SYNTAX Uint8
			MAX-ACCESS read-write
			STATUS current
			DESCRIPTION
				"VLAN_REG_1"
		::= { ipa3000c01v2Entry 87 }

		-- 1.3.6.1.4.1.10106.3.101291.1.1.89
		ipa3000c01v2VlanRx1Reg2 OBJECT-TYPE
			SYNTAX Uint8
			MAX-ACCESS read-write
			STATUS current
			DESCRIPTION
				"VLAN_REG_2"
		::= { ipa3000c01v2Entry 89 }

		-- 1.3.6.1.4.1.10106.3.101291.1.1.91
		ipa3000c01v2Str2UipDAdd3 OBJECT-TYPE
			SYNTAX Uint8
			MAX-ACCESS read-write
			STATUS current
			DESCRIPTION
				"Unicast IP address (3)"
		::= { ipa3000c01v2Entry 91 }

		-- 1.3.6.1.4.1.10106.3.101291.1.1.93
		ipa3000c01v2Str2UipDAdd2 OBJECT-TYPE
			SYNTAX Uint8
			MAX-ACCESS read-write
			STATUS current
			DESCRIPTION
				"Unicast IP address (2)"
		::= { ipa3000c01v2Entry 93 }

		-- 1.3.6.1.4.1.10106.3.101291.1.1.95
		ipa3000c01v2Str2UipDAdd1 OBJECT-TYPE
			SYNTAX Uint8
			MAX-ACCESS read-write
			STATUS current
			DESCRIPTION
				"Unicast IP address (1)"
		::= { ipa3000c01v2Entry 95 }

		-- 1.3.6.1.4.1.10106.3.101291.1.1.97
		ipa3000c01v2Str2UipDAdd0 OBJECT-TYPE
			SYNTAX Uint8
			MAX-ACCESS read-write
			STATUS current
			DESCRIPTION
				"Unicast IP address (0)"
		::= { ipa3000c01v2Entry 97 }

		-- 1.3.6.1.4.1.10106.3.101291.1.1.99
		ipa3000c01v2Str2MipDAdd3 OBJECT-TYPE
			SYNTAX Uint8
			MAX-ACCESS read-write
			STATUS current
			DESCRIPTION
				"Multicast IP address (3)"
		::= { ipa3000c01v2Entry 99 }

		-- 1.3.6.1.4.1.10106.3.101291.1.1.101
		ipa3000c01v2Str2MipDAdd2 OBJECT-TYPE
			SYNTAX Uint8
			MAX-ACCESS read-write
			STATUS current
			DESCRIPTION
				"Multicast IP address (2)"
		::= { ipa3000c01v2Entry 101 }

		-- 1.3.6.1.4.1.10106.3.101291.1.1.103
		ipa3000c01v2Str2MipDAdd1 OBJECT-TYPE
			SYNTAX Uint8
			MAX-ACCESS read-write
			STATUS current
			DESCRIPTION
				"Multicast IP address (1)"
		::= { ipa3000c01v2Entry 103 }

		-- 1.3.6.1.4.1.10106.3.101291.1.1.105
		ipa3000c01v2Str2MipDAdd0 OBJECT-TYPE
			SYNTAX Uint8
			MAX-ACCESS read-write
			STATUS current
			DESCRIPTION
				"Multicast IP address (0)"
		::= { ipa3000c01v2Entry 105 }

		-- 1.3.6.1.4.1.10106.3.101291.1.1.107
		ipa3000c01v2Str2DPortMsb OBJECT-TYPE
			SYNTAX Uint8
			MAX-ACCESS read-write
			STATUS current
			DESCRIPTION
				"Destination port (msb)"
		::= { ipa3000c01v2Entry 107 }

		-- 1.3.6.1.4.1.10106.3.101291.1.1.109
		ipa3000c01v2Str2DPortLsb OBJECT-TYPE
			SYNTAX Uint8
			MAX-ACCESS read-write
			STATUS current
			DESCRIPTION
				"Destination port (lsb)"
		::= { ipa3000c01v2Entry 109 }

		-- 1.3.6.1.4.1.10106.3.101291.1.1.111
		ipa3000c01v2Str2FecEna OBJECT-TYPE
			SYNTAX Bit0No1Yes
			MAX-ACCESS read-write
			STATUS current
			DESCRIPTION
				"Enable FEC"
		::= { ipa3000c01v2Entry 111 }

		-- 1.3.6.1.4.1.10106.3.101291.1.1.113
		ipa3000c01v2Str2MulticEna OBJECT-TYPE
			SYNTAX IpaTxMode
			MAX-ACCESS read-write
			STATUS current
			DESCRIPTION
				"RX mode"
		::= { ipa3000c01v2Entry 113 }

		-- 1.3.6.1.4.1.10106.3.101291.1.1.115
		ipa3000c01v2VlanRx2Enable OBJECT-TYPE
			SYNTAX Bit0No1Yes
			MAX-ACCESS read-write
			STATUS current
			DESCRIPTION
				"VLAN Enable"
		::= { ipa3000c01v2Entry 115 }

		-- 1.3.6.1.4.1.10106.3.101291.1.1.117
		ipa3000c01v2VlanRx2Reg1 OBJECT-TYPE
			SYNTAX Uint8
			MAX-ACCESS read-write
			STATUS current
			DESCRIPTION
				"VLAN_REG_1"
		::= { ipa3000c01v2Entry 117 }

		-- 1.3.6.1.4.1.10106.3.101291.1.1.119
		ipa3000c01v2VlanRx2Reg2 OBJECT-TYPE
			SYNTAX Uint8
			MAX-ACCESS read-write
			STATUS current
			DESCRIPTION
				"VLAN_REG_2"
		::= { ipa3000c01v2Entry 119 }

		-- 1.3.6.1.4.1.10106.3.101291.1.1.121
		ipa3000c01v2TxUniEna OBJECT-TYPE
			SYNTAX Bit0No1Yes
			MAX-ACCESS read-write
			STATUS current
			DESCRIPTION
				"Enable TX"
		::= { ipa3000c01v2Entry 121 }

		-- 1.3.6.1.4.1.10106.3.101291.1.1.123
		ipa3000c01v2TxMultiEna OBJECT-TYPE
			SYNTAX IpaTxMode
			MAX-ACCESS read-write
			STATUS current
			DESCRIPTION
				"TX mode"
		::= { ipa3000c01v2Entry 123 }

		-- 1.3.6.1.4.1.10106.3.101291.1.1.125
		ipa3000c01v2LocalIpAdd3 OBJECT-TYPE
			SYNTAX Uint8
			MAX-ACCESS read-write
			STATUS current
			DESCRIPTION
				"Unicast IP address (3)"
		::= { ipa3000c01v2Entry 125 }

		-- 1.3.6.1.4.1.10106.3.101291.1.1.127
		ipa3000c01v2LocalIpAdd2 OBJECT-TYPE
			SYNTAX Uint8
			MAX-ACCESS read-write
			STATUS current
			DESCRIPTION
				"Unicast IP address (2)"
		::= { ipa3000c01v2Entry 127 }

		-- 1.3.6.1.4.1.10106.3.101291.1.1.129
		ipa3000c01v2LocalIpAdd1 OBJECT-TYPE
			SYNTAX Uint8
			MAX-ACCESS read-write
			STATUS current
			DESCRIPTION
				"Unicast IP address (1)"
		::= { ipa3000c01v2Entry 129 }

		-- 1.3.6.1.4.1.10106.3.101291.1.1.131
		ipa3000c01v2LocalIpAdd0 OBJECT-TYPE
			SYNTAX Uint8
			MAX-ACCESS read-write
			STATUS current
			DESCRIPTION
				"Unicast IP address (0)"
		::= { ipa3000c01v2Entry 131 }

		-- 1.3.6.1.4.1.10106.3.101291.1.1.133
		ipa3000c01v2LocalIpMask3 OBJECT-TYPE
			SYNTAX Uint8
			MAX-ACCESS read-write
			STATUS current
			DESCRIPTION
				"IP mask (3)"
		::= { ipa3000c01v2Entry 133 }

		-- 1.3.6.1.4.1.10106.3.101291.1.1.135
		ipa3000c01v2LocalIpMask2 OBJECT-TYPE
			SYNTAX Uint8
			MAX-ACCESS read-write
			STATUS current
			DESCRIPTION
				"IP mask (2)"
		::= { ipa3000c01v2Entry 135 }

		-- 1.3.6.1.4.1.10106.3.101291.1.1.137
		ipa3000c01v2LocalIpMask1 OBJECT-TYPE
			SYNTAX Uint8
			MAX-ACCESS read-write
			STATUS current
			DESCRIPTION
				"IP mask (1)"
		::= { ipa3000c01v2Entry 137 }

		-- 1.3.6.1.4.1.10106.3.101291.1.1.139
		ipa3000c01v2LocalIpMask0 OBJECT-TYPE
			SYNTAX Uint8
			MAX-ACCESS read-write
			STATUS current
			DESCRIPTION
				"IP mask (0)"
		::= { ipa3000c01v2Entry 139 }

		-- 1.3.6.1.4.1.10106.3.101291.1.1.141
		ipa3000c01v2LocalIpGway3 OBJECT-TYPE
			SYNTAX Uint8
			MAX-ACCESS read-write
			STATUS current
			DESCRIPTION
				"Gateway IP address (3)"
		::= { ipa3000c01v2Entry 141 }

		-- 1.3.6.1.4.1.10106.3.101291.1.1.143
		ipa3000c01v2LocalIpGway2 OBJECT-TYPE
			SYNTAX Uint8
			MAX-ACCESS read-write
			STATUS current
			DESCRIPTION
				"Gateway IP address (2)"
		::= { ipa3000c01v2Entry 143 }

		-- 1.3.6.1.4.1.10106.3.101291.1.1.145
		ipa3000c01v2LocalIpGway1 OBJECT-TYPE
			SYNTAX Uint8
			MAX-ACCESS read-write
			STATUS current
			DESCRIPTION
				"Gateway IP address (1)"
		::= { ipa3000c01v2Entry 145 }

		-- 1.3.6.1.4.1.10106.3.101291.1.1.147
		ipa3000c01v2LocalIpGway0 OBJECT-TYPE
			SYNTAX Uint8
			MAX-ACCESS read-write
			STATUS current
			DESCRIPTION
				"Gateway IP address (0)"
		::= { ipa3000c01v2Entry 147 }

		-- 1.3.6.1.4.1.10106.3.101291.1.1.149
		ipa3000c01v2TxUipAdd3 OBJECT-TYPE
			SYNTAX Uint8
			MAX-ACCESS read-write
			STATUS current
			DESCRIPTION
				"Destination IP address (3)"
		::= { ipa3000c01v2Entry 149 }

		-- 1.3.6.1.4.1.10106.3.101291.1.1.151
		ipa3000c01v2TxUipAdd2 OBJECT-TYPE
			SYNTAX Uint8
			MAX-ACCESS read-write
			STATUS current
			DESCRIPTION
				"Destination IP address (2)"
		::= { ipa3000c01v2Entry 151 }

		-- 1.3.6.1.4.1.10106.3.101291.1.1.153
		ipa3000c01v2TxUipAdd1 OBJECT-TYPE
			SYNTAX Uint8
			MAX-ACCESS read-write
			STATUS current
			DESCRIPTION
				"Destination IP address (1)"
		::= { ipa3000c01v2Entry 153 }

		-- 1.3.6.1.4.1.10106.3.101291.1.1.155
		ipa3000c01v2TxUipAdd0 OBJECT-TYPE
			SYNTAX Uint8
			MAX-ACCESS read-write
			STATUS current
			DESCRIPTION
				"Destination IP address (0)"
		::= { ipa3000c01v2Entry 155 }

		-- 1.3.6.1.4.1.10106.3.101291.1.1.157
		ipa3000c01v2TxMipAdd3 OBJECT-TYPE
			SYNTAX Uint8
			MAX-ACCESS read-write
			STATUS current
			DESCRIPTION
				"Multicast dest. IP address (3)"
		::= { ipa3000c01v2Entry 157 }

		-- 1.3.6.1.4.1.10106.3.101291.1.1.159
		ipa3000c01v2TxMipAdd2 OBJECT-TYPE
			SYNTAX Uint8
			MAX-ACCESS read-write
			STATUS current
			DESCRIPTION
				"Multicast dest. IP address (2)"
		::= { ipa3000c01v2Entry 159 }

		-- 1.3.6.1.4.1.10106.3.101291.1.1.161
		ipa3000c01v2TxMipAdd1 OBJECT-TYPE
			SYNTAX Uint8
			MAX-ACCESS read-write
			STATUS current
			DESCRIPTION
				"Multicast dest. IP address (1)"
		::= { ipa3000c01v2Entry 161 }

		-- 1.3.6.1.4.1.10106.3.101291.1.1.163
		ipa3000c01v2TxMipAdd0 OBJECT-TYPE
			SYNTAX Uint8
			MAX-ACCESS read-write
			STATUS current
			DESCRIPTION
				"Multicast dest. IP address (0)"
		::= { ipa3000c01v2Entry 163 }

		-- 1.3.6.1.4.1.10106.3.101291.1.1.165
		ipa3000c01v2TxSPortMsb OBJECT-TYPE
			SYNTAX Uint8
			MAX-ACCESS read-write
			STATUS current
			DESCRIPTION
				"Source port (msb)"
		::= { ipa3000c01v2Entry 165 }

		-- 1.3.6.1.4.1.10106.3.101291.1.1.167
		ipa3000c01v2TxSPortLsb OBJECT-TYPE
			SYNTAX Uint8
			MAX-ACCESS read-write
			STATUS current
			DESCRIPTION
				"Source port (lsb)"
		::= { ipa3000c01v2Entry 167 }

		-- 1.3.6.1.4.1.10106.3.101291.1.1.169
		ipa3000c01v2TxDPortMsb OBJECT-TYPE
			SYNTAX Uint8
			MAX-ACCESS read-write
			STATUS current
			DESCRIPTION
				"Destination port (msb)"
		::= { ipa3000c01v2Entry 169 }

		-- 1.3.6.1.4.1.10106.3.101291.1.1.171
		ipa3000c01v2TxDPortLsb OBJECT-TYPE
			SYNTAX Uint8
			MAX-ACCESS read-write
			STATUS current
			DESCRIPTION
				"Destination port (lsb)"
		::= { ipa3000c01v2Entry 171 }

		-- 1.3.6.1.4.1.10106.3.101291.1.1.173
		ipa3000c01v2VlanTxEnable OBJECT-TYPE
			SYNTAX Bit0No1Yes
			MAX-ACCESS read-write
			STATUS current
			DESCRIPTION
				"VLAN Enable"
		::= { ipa3000c01v2Entry 173 }

		-- 1.3.6.1.4.1.10106.3.101291.1.1.175
		ipa3000c01v2VlanTxPriority OBJECT-TYPE
			SYNTAX Uint3
			MAX-ACCESS read-write
			STATUS current
			DESCRIPTION
				"VLAN Priority"
		::= { ipa3000c01v2Entry 175 }

		-- 1.3.6.1.4.1.10106.3.101291.1.1.177
		ipa3000c01v2VlanTxReg1 OBJECT-TYPE
			SYNTAX Uint8
			MAX-ACCESS read-write
			STATUS current
			DESCRIPTION
				"VLAN_REG_1"
		::= { ipa3000c01v2Entry 177 }

		-- 1.3.6.1.4.1.10106.3.101291.1.1.179
		ipa3000c01v2VlanTxReg2 OBJECT-TYPE
			SYNTAX Uint8
			MAX-ACCESS read-write
			STATUS current
			DESCRIPTION
				"VLAN_REG_2"
		::= { ipa3000c01v2Entry 179 }

		-- 1.3.6.1.4.1.10106.3.101291.1.1.181
		ipa3000c01v2TxLParam OBJECT-TYPE
			SYNTAX Uint5
			MAX-ACCESS read-write
			STATUS current
			DESCRIPTION
				"L parameter (FEC mode columns)"
		::= { ipa3000c01v2Entry 181 }

		-- 1.3.6.1.4.1.10106.3.101291.1.1.183
		ipa3000c01v2TxFecMode OBJECT-TYPE
			SYNTAX FecMode
			MAX-ACCESS read-write
			STATUS current
			DESCRIPTION
				"Protocol"
		::= { ipa3000c01v2Entry 183 }

		-- 1.3.6.1.4.1.10106.3.101291.1.1.185
		ipa3000c01v2TxDParam OBJECT-TYPE
			SYNTAX Uint5
			MAX-ACCESS read-write
			STATUS current
			DESCRIPTION
				"D parameter (FEC mode rows)"
		::= { ipa3000c01v2Entry 185 }

		-- 1.3.6.1.4.1.10106.3.101291.1.1.187
		ipa3000c01v2TxTspkInIppk OBJECT-TYPE
			SYNTAX Uint3
			MAX-ACCESS read-write
			STATUS current
			DESCRIPTION
				"TS packets in each IP packet"
		::= { ipa3000c01v2Entry 187 }

		-- 1.3.6.1.4.1.10106.3.101291.1.1.189
		ipa3000c01v2TxRowDelay OBJECT-TYPE
			SYNTAX Uint5
			MAX-ACCESS read-write
			STATUS current
			DESCRIPTION
				"FEC row delay"
		::= { ipa3000c01v2Entry 189 }

		-- 1.3.6.1.4.1.10106.3.101291.1.1.191
		ipa3000c01v2TxColDelay OBJECT-TYPE
			SYNTAX Uint8
			MAX-ACCESS read-write
			STATUS current
			DESCRIPTION
				"FEC column delay"
		::= { ipa3000c01v2Entry 191 }

		-- 1.3.6.1.4.1.10106.3.101291.1.1.193
		ipa3000c01v2LowCost OBJECT-TYPE
			SYNTAX Bit0No1Yes
			MAX-ACCESS read-write
			STATUS current
			DESCRIPTION
				"TOS.  Low cost"
		::= { ipa3000c01v2Entry 193 }

		-- 1.3.6.1.4.1.10106.3.101291.1.1.195
		ipa3000c01v2HighReliabilty OBJECT-TYPE
			SYNTAX Bit0No1Yes
			MAX-ACCESS read-write
			STATUS current
			DESCRIPTION
				"TOS. High reliability"
		::= { ipa3000c01v2Entry 195 }

		-- 1.3.6.1.4.1.10106.3.101291.1.1.197
		ipa3000c01v2HighThroughput OBJECT-TYPE
			SYNTAX Bit0No1Yes
			MAX-ACCESS read-write
			STATUS current
			DESCRIPTION
				"TOS. High Throughput"
		::= { ipa3000c01v2Entry 197 }

		-- 1.3.6.1.4.1.10106.3.101291.1.1.199
		ipa3000c01v2LowDelay OBJECT-TYPE
			SYNTAX Bit0No1Yes
			MAX-ACCESS read-write
			STATUS current
			DESCRIPTION
				"TOS. Low delay"
		::= { ipa3000c01v2Entry 199 }

		-- 1.3.6.1.4.1.10106.3.101291.1.1.201
		ipa3000c01v2Precedence OBJECT-TYPE
			SYNTAX IpaPrecedence
			MAX-ACCESS read-write
			STATUS current
			DESCRIPTION
				"TOS. Precedence"
		::= { ipa3000c01v2Entry 201 }

		-- 1.3.6.1.4.1.10106.3.101291.1.1.203
		ipa3000c01v2Ttl OBJECT-TYPE
			SYNTAX Uint8
			MAX-ACCESS read-write
			STATUS current
			DESCRIPTION
				"Time to live"
		::= { ipa3000c01v2Entry 203 }

		-- 1.3.6.1.4.1.10106.3.101291.1.1.205
		ipa3000c01v2Str1IgmFAdd3 OBJECT-TYPE
			SYNTAX Uint8
			MAX-ACCESS read-write
			STATUS current
			DESCRIPTION
				"Source IP address (3)"
		::= { ipa3000c01v2Entry 205 }

		-- 1.3.6.1.4.1.10106.3.101291.1.1.207
		ipa3000c01v2Str1IgmFAdd2 OBJECT-TYPE
			SYNTAX Uint8
			MAX-ACCESS read-write
			STATUS current
			DESCRIPTION
				"Source IP address (2)"
		::= { ipa3000c01v2Entry 207 }

		-- 1.3.6.1.4.1.10106.3.101291.1.1.209
		ipa3000c01v2Str1IgmFAdd1 OBJECT-TYPE
			SYNTAX Uint8
			MAX-ACCESS read-write
			STATUS current
			DESCRIPTION
				"Source IP address (1)"
		::= { ipa3000c01v2Entry 209 }

		-- 1.3.6.1.4.1.10106.3.101291.1.1.211
		ipa3000c01v2Str1IgmFAdd0 OBJECT-TYPE
			SYNTAX Uint8
			MAX-ACCESS read-write
			STATUS current
			DESCRIPTION
				"Source IP address (0)"
		::= { ipa3000c01v2Entry 211 }

		-- 1.3.6.1.4.1.10106.3.101291.1.1.213
		ipa3000c01v2Str2IgmFAdd3 OBJECT-TYPE
			SYNTAX Uint8
			MAX-ACCESS read-write
			STATUS current
			DESCRIPTION
				"Source IP address (3)"
		::= { ipa3000c01v2Entry 213 }

		-- 1.3.6.1.4.1.10106.3.101291.1.1.215
		ipa3000c01v2Str2IgmFAdd2 OBJECT-TYPE
			SYNTAX Uint8
			MAX-ACCESS read-write
			STATUS current
			DESCRIPTION
				"Source IP address (2)"
		::= { ipa3000c01v2Entry 215 }

		-- 1.3.6.1.4.1.10106.3.101291.1.1.217
		ipa3000c01v2Str2IgmFAdd1 OBJECT-TYPE
			SYNTAX Uint8
			MAX-ACCESS read-write
			STATUS current
			DESCRIPTION
				"Source IP address (1)"
		::= { ipa3000c01v2Entry 217 }

		-- 1.3.6.1.4.1.10106.3.101291.1.1.219
		ipa3000c01v2Str2IgmFAdd0 OBJECT-TYPE
			SYNTAX Uint8
			MAX-ACCESS read-write
			STATUS current
			DESCRIPTION
				"Source IP address (0)"
		::= { ipa3000c01v2Entry 219 }

		-- 1.3.6.1.4.1.10106.3.101291.1.1.221
		ipa3000c01v21ppsFail OBJECT-TYPE
			SYNTAX BitFail
			MAX-ACCESS read-only
			STATUS current
			DESCRIPTION
				"1PPS reference input status"
		::= { ipa3000c01v2Entry 221 }

		-- 1.3.6.1.4.1.10106.3.101291.1.1.222
		ipa3000c01v21ppsFailTrapEnable OBJECT-TYPE
			SYNTAX AlarmEnable
			MAX-ACCESS read-write
			STATUS current
			DESCRIPTION
				"1PPS reference input status Trap Enable"
		::= { ipa3000c01v2Entry 222 }

		-- 1.3.6.1.4.1.10106.3.101291.1.1.223
		ipa3000c01v210mhzFail OBJECT-TYPE
			SYNTAX BitFail
			MAX-ACCESS read-only
			STATUS current
			DESCRIPTION
				"10MHz reference input status"
		::= { ipa3000c01v2Entry 223 }

		-- 1.3.6.1.4.1.10106.3.101291.1.1.224
		ipa3000c01v210mhzFailTrapEnable OBJECT-TYPE
			SYNTAX AlarmEnable
			MAX-ACCESS read-write
			STATUS current
			DESCRIPTION
				"10MHz reference input status Trap Enable"
		::= { ipa3000c01v2Entry 224 }

		-- 1.3.6.1.4.1.10106.3.101291.1.1.225
		ipa3000c01v2OutputFail OBJECT-TYPE
			SYNTAX BitFail
			MAX-ACCESS read-only
			STATUS current
			DESCRIPTION
				"The output signal is not valid because all inputs failed"
		::= { ipa3000c01v2Entry 225 }

		-- 1.3.6.1.4.1.10106.3.101291.1.1.226
		ipa3000c01v2OutputFailTrapEnable OBJECT-TYPE
			SYNTAX AlarmEnable
			MAX-ACCESS read-write
			STATUS current
			DESCRIPTION
				"The output signal is not valid because all inputs failed Trap Enable"
		::= { ipa3000c01v2Entry 226 }

		-- 1.3.6.1.4.1.10106.3.101291.1.1.227
		ipa3000c01v2AsiMainDelWar OBJECT-TYPE
			SYNTAX BitFail
			MAX-ACCESS read-only
			STATUS current
			DESCRIPTION
				"The ASI main delay is greater than the programmed output delay"
		::= { ipa3000c01v2Entry 227 }

		-- 1.3.6.1.4.1.10106.3.101291.1.1.228
		ipa3000c01v2AsiMainDelWarTrapEnable OBJECT-TYPE
			SYNTAX AlarmEnable
			MAX-ACCESS read-write
			STATUS current
			DESCRIPTION
				"The ASI main delay is greater than the programmed output delay Trap Enable"
		::= { ipa3000c01v2Entry 228 }

		-- 1.3.6.1.4.1.10106.3.101291.1.1.229
		ipa3000c01v2AsiResDelWar OBJECT-TYPE
			SYNTAX BitFail
			MAX-ACCESS read-only
			STATUS current
			DESCRIPTION
				"The ASI reserve delay is greater than the programmed output delay"
		::= { ipa3000c01v2Entry 229 }

		-- 1.3.6.1.4.1.10106.3.101291.1.1.230
		ipa3000c01v2AsiResDelWarTrapEnable OBJECT-TYPE
			SYNTAX AlarmEnable
			MAX-ACCESS read-write
			STATUS current
			DESCRIPTION
				"The ASI reserve delay is greater than the programmed output delay Trap Enable"
		::= { ipa3000c01v2Entry 230 }

		-- 1.3.6.1.4.1.10106.3.101291.1.1.231
		ipa3000c01v2IpMainDelWar OBJECT-TYPE
			SYNTAX BitFail
			MAX-ACCESS read-only
			STATUS current
			DESCRIPTION
				"The IP main delay is greater than the programmed output delay"
		::= { ipa3000c01v2Entry 231 }

		-- 1.3.6.1.4.1.10106.3.101291.1.1.232
		ipa3000c01v2IpMainDelWarTrapEnable OBJECT-TYPE
			SYNTAX AlarmEnable
			MAX-ACCESS read-write
			STATUS current
			DESCRIPTION
				"The IP main delay is greater than the programmed output delay Trap Enable"
		::= { ipa3000c01v2Entry 232 }

		-- 1.3.6.1.4.1.10106.3.101291.1.1.233
		ipa3000c01v2IpResDelWar OBJECT-TYPE
			SYNTAX BitFail
			MAX-ACCESS read-only
			STATUS current
			DESCRIPTION
				"The IP reserve delay is greater than the programmed output delay"
		::= { ipa3000c01v2Entry 233 }

		-- 1.3.6.1.4.1.10106.3.101291.1.1.234
		ipa3000c01v2IpResDelWarTrapEnable OBJECT-TYPE
			SYNTAX AlarmEnable
			MAX-ACCESS read-write
			STATUS current
			DESCRIPTION
				"The IP reserve delay is greater than the programmed output delay Trap Enable"
		::= { ipa3000c01v2Entry 234 }

		-- 1.3.6.1.4.1.10106.3.101291.1.1.235
		ipa3000c01v2AsiMainFail OBJECT-TYPE
			SYNTAX BitFail
			MAX-ACCESS read-only
			STATUS current
			DESCRIPTION
				"ASI main input status"
		::= { ipa3000c01v2Entry 235 }

		-- 1.3.6.1.4.1.10106.3.101291.1.1.236
		ipa3000c01v2AsiMainFailTrapEnable OBJECT-TYPE
			SYNTAX AlarmEnable
			MAX-ACCESS read-write
			STATUS current
			DESCRIPTION
				"ASI main input status Trap Enable"
		::= { ipa3000c01v2Entry 236 }

		-- 1.3.6.1.4.1.10106.3.101291.1.1.237
		ipa3000c01v2ExAsiMainFail OBJECT-TYPE
			SYNTAX BitFail
			MAX-ACCESS read-only
			STATUS current
			DESCRIPTION
				"ASI main external input fail status"
		::= { ipa3000c01v2Entry 237 }

		-- 1.3.6.1.4.1.10106.3.101291.1.1.238
		ipa3000c01v2ExAsiMainFailTrapEnable OBJECT-TYPE
			SYNTAX AlarmEnable
			MAX-ACCESS read-write
			STATUS current
			DESCRIPTION
				"ASI main external input fail status Trap Enable"
		::= { ipa3000c01v2Entry 238 }

		-- 1.3.6.1.4.1.10106.3.101291.1.1.239
		ipa3000c01v2AsiResFail OBJECT-TYPE
			SYNTAX BitFail
			MAX-ACCESS read-only
			STATUS current
			DESCRIPTION
				"ASI reserve input status"
		::= { ipa3000c01v2Entry 239 }

		-- 1.3.6.1.4.1.10106.3.101291.1.1.240
		ipa3000c01v2AsiResFailTrapEnable OBJECT-TYPE
			SYNTAX AlarmEnable
			MAX-ACCESS read-write
			STATUS current
			DESCRIPTION
				"ASI reserve input status Trap Enable"
		::= { ipa3000c01v2Entry 240 }

		-- 1.3.6.1.4.1.10106.3.101291.1.1.241
		ipa3000c01v2ExAsiResFail OBJECT-TYPE
			SYNTAX BitFail
			MAX-ACCESS read-only
			STATUS current
			DESCRIPTION
				"ASI reserve external input fail status"
		::= { ipa3000c01v2Entry 241 }

		-- 1.3.6.1.4.1.10106.3.101291.1.1.242
		ipa3000c01v2ExAsiResFailTrapEnable OBJECT-TYPE
			SYNTAX AlarmEnable
			MAX-ACCESS read-write
			STATUS current
			DESCRIPTION
				"ASI reserve external input fail status Trap Enable"
		::= { ipa3000c01v2Entry 242 }

		-- 1.3.6.1.4.1.10106.3.101291.1.1.243
		ipa3000c01v2IpMainFail OBJECT-TYPE
			SYNTAX BitFail
			MAX-ACCESS read-only
			STATUS current
			DESCRIPTION
				"IP main input status"
		::= { ipa3000c01v2Entry 243 }

		-- 1.3.6.1.4.1.10106.3.101291.1.1.244
		ipa3000c01v2IpMainFailTrapEnable OBJECT-TYPE
			SYNTAX AlarmEnable
			MAX-ACCESS read-write
			STATUS current
			DESCRIPTION
				"IP main input status Trap Enable"
		::= { ipa3000c01v2Entry 244 }

		-- 1.3.6.1.4.1.10106.3.101291.1.1.245
		ipa3000c01v2ExIpMainFail OBJECT-TYPE
			SYNTAX BitFail
			MAX-ACCESS read-only
			STATUS current
			DESCRIPTION
				"IP main external input fail status"
		::= { ipa3000c01v2Entry 245 }

		-- 1.3.6.1.4.1.10106.3.101291.1.1.246
		ipa3000c01v2ExIpMainFailTrapEnable OBJECT-TYPE
			SYNTAX AlarmEnable
			MAX-ACCESS read-write
			STATUS current
			DESCRIPTION
				"IP main external input fail status Trap Enable"
		::= { ipa3000c01v2Entry 246 }

		-- 1.3.6.1.4.1.10106.3.101291.1.1.247
		ipa3000c01v2IpResFail OBJECT-TYPE
			SYNTAX BitFail
			MAX-ACCESS read-only
			STATUS current
			DESCRIPTION
				"IP reserve input status"
		::= { ipa3000c01v2Entry 247 }

		-- 1.3.6.1.4.1.10106.3.101291.1.1.248
		ipa3000c01v2IpResFailTrapEnable OBJECT-TYPE
			SYNTAX AlarmEnable
			MAX-ACCESS read-write
			STATUS current
			DESCRIPTION
				"IP reserve input status Trap Enable"
		::= { ipa3000c01v2Entry 248 }

		-- 1.3.6.1.4.1.10106.3.101291.1.1.249
		ipa3000c01v2ExIpResFail OBJECT-TYPE
			SYNTAX BitFail
			MAX-ACCESS read-only
			STATUS current
			DESCRIPTION
				"IP reserve external input fail status"
		::= { ipa3000c01v2Entry 249 }

		-- 1.3.6.1.4.1.10106.3.101291.1.1.250
		ipa3000c01v2ExIpResFailTrapEnable OBJECT-TYPE
			SYNTAX AlarmEnable
			MAX-ACCESS read-write
			STATUS current
			DESCRIPTION
				"IP reserve external input fail status Trap Enable"
		::= { ipa3000c01v2Entry 250 }

		-- 1.3.6.1.4.1.10106.3.101291.1.1.251
		ipa3000c01v2AsimAsirSeam OBJECT-TYPE
			SYNTAX Bit0Sea1Nse
			MAX-ACCESS read-only
			STATUS current
			DESCRIPTION
				"ASI main to ASI reserve seamles switching capability"
		::= { ipa3000c01v2Entry 251 }

		-- 1.3.6.1.4.1.10106.3.101291.1.1.253
		ipa3000c01v2AsimIpmSeam OBJECT-TYPE
			SYNTAX Bit0Sea1Nse
			MAX-ACCESS read-only
			STATUS current
			DESCRIPTION
				"ASI main to IP main seamles switching capability"
		::= { ipa3000c01v2Entry 253 }

		-- 1.3.6.1.4.1.10106.3.101291.1.1.255
		ipa3000c01v2AsimIprSeam OBJECT-TYPE
			SYNTAX Bit0Sea1Nse
			MAX-ACCESS read-only
			STATUS current
			DESCRIPTION
				"ASI main to IP reserve seamles switching capability"
		::= { ipa3000c01v2Entry 255 }

		-- 1.3.6.1.4.1.10106.3.101291.1.1.257
		ipa3000c01v2AsirIpmSeam OBJECT-TYPE
			SYNTAX Bit0Sea1Nse
			MAX-ACCESS read-only
			STATUS current
			DESCRIPTION
				"ASI reserve to IP main seamles switching capability"
		::= { ipa3000c01v2Entry 257 }

		-- 1.3.6.1.4.1.10106.3.101291.1.1.259
		ipa3000c01v2AsirIprSeam OBJECT-TYPE
			SYNTAX Bit0Sea1Nse
			MAX-ACCESS read-only
			STATUS current
			DESCRIPTION
				"ASI reserve to IP reserve seamles switching capability"
		::= { ipa3000c01v2Entry 259 }

		-- 1.3.6.1.4.1.10106.3.101291.1.1.261
		ipa3000c01v2IpmIprSeam OBJECT-TYPE
			SYNTAX Bit0Sea1Nse
			MAX-ACCESS read-only
			STATUS current
			DESCRIPTION
				"IP main to IP reserve seamles switching capability"
		::= { ipa3000c01v2Entry 261 }

		-- 1.3.6.1.4.1.10106.3.101291.1.1.263
		ipa3000c01v2GlobalSeam OBJECT-TYPE
			SYNTAX Bit0Sea1Nse
			MAX-ACCESS read-only
			STATUS current
			DESCRIPTION
				"Global seamles switching capability"
		::= { ipa3000c01v2Entry 263 }

		-- 1.3.6.1.4.1.10106.3.101291.1.1.264
		ipa3000c01v2GlobalSeamTrapEnable OBJECT-TYPE
			SYNTAX AlarmEnable
			MAX-ACCESS read-write
			STATUS current
			DESCRIPTION
				"Global seamles switching capability Trap Enable"
		::= { ipa3000c01v2Entry 264 }

		-- 1.3.6.1.4.1.10106.3.101291.1.1.265
		ipa3000c01v2AsiMainDelay OBJECT-TYPE
			SYNTAX DelayX65Ms
			MAX-ACCESS read-only
			STATUS current
			DESCRIPTION
				"DVB-T mode: input delay refered to 1PPS reference"
		::= { ipa3000c01v2Entry 265 }

		-- 1.3.6.1.4.1.10106.3.101291.1.1.267
		ipa3000c01v2AsiResDelay OBJECT-TYPE
			SYNTAX DelayX65Ms
			MAX-ACCESS read-only
			STATUS current
			DESCRIPTION
				"DVB-T mode: input delay refered to 1PPS reference"
		::= { ipa3000c01v2Entry 267 }

		-- 1.3.6.1.4.1.10106.3.101291.1.1.269
		ipa3000c01v2IpMainDelay OBJECT-TYPE
			SYNTAX DelayX65Ms
			MAX-ACCESS read-only
			STATUS current
			DESCRIPTION
				"DVB-T mode: input delay refered to 1PPS reference"
		::= { ipa3000c01v2Entry 269 }

		-- 1.3.6.1.4.1.10106.3.101291.1.1.271
		ipa3000c01v2IpResDelay OBJECT-TYPE
			SYNTAX DelayX65Ms
			MAX-ACCESS read-only
			STATUS current
			DESCRIPTION
				"DVB-T mode: input delay refered to 1PPS reference"
		::= { ipa3000c01v2Entry 271 }

		-- 1.3.6.1.4.1.10106.3.101291.1.1.273
		ipa3000c01v2IpRxAddress3 OBJECT-TYPE
			SYNTAX Uint8
			MAX-ACCESS read-only
			STATUS current
			DESCRIPTION
				"RX packets source IP address (3)"
		::= { ipa3000c01v2Entry 273 }

		-- 1.3.6.1.4.1.10106.3.101291.1.1.275
		ipa3000c01v2IpRxAddress2 OBJECT-TYPE
			SYNTAX Uint8
			MAX-ACCESS read-only
			STATUS current
			DESCRIPTION
				"RX packets source IP address (2)"
		::= { ipa3000c01v2Entry 275 }

		-- 1.3.6.1.4.1.10106.3.101291.1.1.277
		ipa3000c01v2IpRxAddress1 OBJECT-TYPE
			SYNTAX Uint8
			MAX-ACCESS read-only
			STATUS current
			DESCRIPTION
				"RX packets source IP address (1)"
		::= { ipa3000c01v2Entry 277 }

		-- 1.3.6.1.4.1.10106.3.101291.1.1.279
		ipa3000c01v2IpRxAddress0 OBJECT-TYPE
			SYNTAX Uint8
			MAX-ACCESS read-only
			STATUS current
			DESCRIPTION
				"RX packets source IP address (0)"
		::= { ipa3000c01v2Entry 279 }

		-- 1.3.6.1.4.1.10106.3.101291.1.1.281
		ipa3000c01v2IpRxPort OBJECT-TYPE
			SYNTAX Uint16
			MAX-ACCESS read-only
			STATUS current
			DESCRIPTION
				"RX packets UDP source port"
		::= { ipa3000c01v2Entry 281 }

		-- 1.3.6.1.4.1.10106.3.101291.1.1.283
		ipa3000c01v2LParam OBJECT-TYPE
			SYNTAX Uint5
			MAX-ACCESS read-only
			STATUS current
			DESCRIPTION
				"L parameter (FEC mode columns)"
		::= { ipa3000c01v2Entry 283 }

		-- 1.3.6.1.4.1.10106.3.101291.1.1.285
		ipa3000c01v2FecMode OBJECT-TYPE
			SYNTAX FecMode
			MAX-ACCESS read-only
			STATUS current
			DESCRIPTION
				"Protocol"
		::= { ipa3000c01v2Entry 285 }

		-- 1.3.6.1.4.1.10106.3.101291.1.1.287
		ipa3000c01v2PacketSize OBJECT-TYPE
			SYNTAX Bit02041188
			MAX-ACCESS read-only
			STATUS current
			DESCRIPTION
				"Bytes in TS packets"
		::= { ipa3000c01v2Entry 287 }

		-- 1.3.6.1.4.1.10106.3.101291.1.1.289
		ipa3000c01v2DParam OBJECT-TYPE
			SYNTAX Uint5
			MAX-ACCESS read-only
			STATUS current
			DESCRIPTION
				"D parameter (FEC mode rows)"
		::= { ipa3000c01v2Entry 289 }

		-- 1.3.6.1.4.1.10106.3.101291.1.1.291
		ipa3000c01v2TsPckInIpPck OBJECT-TYPE
			SYNTAX Uint3
			MAX-ACCESS read-only
			STATUS current
			DESCRIPTION
				"TS packets in each IP packet"
		::= { ipa3000c01v2Entry 291 }

		-- 1.3.6.1.4.1.10106.3.101291.1.1.293
		ipa3000c01v2PacketRate OBJECT-TYPE
			SYNTAX PacketRate
			MAX-ACCESS read-only
			STATUS current
			DESCRIPTION
				"IP packet rate"
		::= { ipa3000c01v2Entry 293 }

		-- 1.3.6.1.4.1.10106.3.101291.1.1.295
		ipa3000c01v2TimeSinceReset OBJECT-TYPE
			SYNTAX TimeS4
			MAX-ACCESS read-only
			STATUS current
			DESCRIPTION
				"Elapsed time from last reset"
		::= { ipa3000c01v2Entry 295 }

		-- 1.3.6.1.4.1.10106.3.101291.1.1.297
		ipa3000c01v2LostIpPck OBJECT-TYPE
			SYNTAX Uint16
			MAX-ACCESS read-only
			STATUS current
			DESCRIPTION
				"Lost IP packets"
		::= { ipa3000c01v2Entry 297 }

		-- 1.3.6.1.4.1.10106.3.101291.1.1.299
		ipa3000c01v2RecoveredIpPck OBJECT-TYPE
			SYNTAX Uint16
			MAX-ACCESS read-only
			STATUS current
			DESCRIPTION
				"Recovered IP packets"
		::= { ipa3000c01v2Entry 299 }

		-- 1.3.6.1.4.1.10106.3.101291.1.1.301
		ipa3000c01v2BadCrcPck OBJECT-TYPE
			SYNTAX Uint16
			MAX-ACCESS read-only
			STATUS current
			DESCRIPTION
				"Bad CRC packets"
		::= { ipa3000c01v2Entry 301 }

		-- 1.3.6.1.4.1.10106.3.101291.1.1.303
		ipa3000c01v2OutOrdIpPck OBJECT-TYPE
			SYNTAX Uint16
			MAX-ACCESS read-only
			STATUS current
			DESCRIPTION
				"Out of order IP packets"
		::= { ipa3000c01v2Entry 303 }

		-- 1.3.6.1.4.1.10106.3.101291.1.1.305
		ipa3000c01v2FecRate OBJECT-TYPE
			SYNTAX PacketRate
			MAX-ACCESS read-only
			STATUS current
			DESCRIPTION
				"FEC packet rate"
		::= { ipa3000c01v2Entry 305 }

		-- 1.3.6.1.4.1.10106.3.101291.1.1.307
		ipa3000c01v2Link OBJECT-TYPE
			SYNTAX IpaEtherStat
			MAX-ACCESS read-only
			STATUS current
			DESCRIPTION
				"Ethernet conection status"
		::= { ipa3000c01v2Entry 307 }

		-- 1.3.6.1.4.1.10106.3.101291.1.1.309
		ipa3000c01v2System OBJECT-TYPE
			SYNTAX IpaEtherSys
			MAX-ACCESS read-only
			STATUS current
			DESCRIPTION
				"Ethernet conection system"
		::= { ipa3000c01v2Entry 309 }

		-- 1.3.6.1.4.1.10106.3.101291.1.1.311
		ipa3000c01v2DestAvailable OBJECT-TYPE
			SYNTAX Bit0No1Yes
			MAX-ACCESS read-only
			STATUS current
			DESCRIPTION
				"Destination IP available"
		::= { ipa3000c01v2Entry 311 }

		-- 1.3.6.1.4.1.10106.3.101291.1.1.313
		ipa3000c01v2BufferStatus OBJECT-TYPE
			SYNTAX Rate1
			MAX-ACCESS read-only
			STATUS current
			DESCRIPTION
				"Buffer filling status in non DVB-T mode"
		::= { ipa3000c01v2Entry 313 }

		-- 1.3.6.1.4.1.10106.3.101291.1.1.315
		ipa3000c01v2PingStatus OBJECT-TYPE
			SYNTAX IpaPingStat
			MAX-ACCESS read-only
			STATUS current
			DESCRIPTION
				"Ping status"
		::= { ipa3000c01v2Entry 315 }

		-- 1.3.6.1.4.1.10106.3.101291.1.1.317
		ipa3000c01v2SerialNo OBJECT-TYPE
			SYNTAX SerialNo
			MAX-ACCESS read-only
			STATUS current
			DESCRIPTION
				"Serial number"
		::= { ipa3000c01v2Entry 317 }

		-- 1.3.6.1.4.1.10106.3.101291.1.1.319
		ipa3000c01v2InpFailMode OBJECT-TYPE
			SYNTAX Bit0Yes1No
			MAX-ACCESS read-write
			STATUS current
			DESCRIPTION
				"Selects if the output is muted when all the inputs fail"
		::= { ipa3000c01v2Entry 319 }

		-- 1.3.6.1.4.1.10106.3.101291.1.1.321
		ipa3000c01v2MaxDelayTxIp OBJECT-TYPE
			SYNTAX TimeX10Ms
			MAX-ACCESS read-write
			STATUS current
			DESCRIPTION
				"Time before starting to transmit after recovering signal"
		::= { ipa3000c01v2Entry 321 }

		-- 1.3.6.1.4.1.10106.3.364801
		hsw3000c01v1 OBJECT IDENTIFIER ::= { albalaProducts 364801 }

		-- 1.3.6.1.4.1.10106.3.364801.1
		hsw3000c01v1Table  OBJECT-TYPE
			SYNTAX SEQUENCE OF Hsw3000c01v1Entry
			MAX-ACCESS not-accessible
			STATUS current
			DESCRIPTION
				"Module  HSW3000C01V1 Table"
			::= { hsw3000c01v1 1 }

		-- 1.3.6.1.4.1.10106.3.364801.1.1
		hsw3000c01v1Entry  OBJECT-TYPE
			SYNTAX Hsw3000c01v1Entry
			MAX-ACCESS not-accessible
			STATUS current
			DESCRIPTION
				"Module HSW3000C01V1 Entry"
			INDEX { hsw3000c01v1Index }
			::= { hsw3000c01v1Table 1 }

			Hsw3000c01v1Entry ::=
			SEQUENCE {
				hsw3000c01v1Index
				ModuleIndex,
				hsw3000c01v1ActivePreset
				PresetActive,
				hsw3000c01v1LoadPreset
				PresetLoad,
				hsw3000c01v1SavePreset
				PresetSave,
				hsw3000c01v1StateSel
				HswState,
				hsw3000c01v1StateSelTrapEnable
				AlarmEnable,
				hsw3000c01v1SwitchMode
				HswSwMode,
				hsw3000c01v1SwitchModeTrapEnable
				AlarmEnable,
				hsw3000c01v1FreezeMode
				HswFreezeMode,
				hsw3000c01v1BypassEnable
				Bit0Dis1Ena,
				hsw3000c01v1BypassEnableTrapEnable
				AlarmEnable,
				hsw3000c01v1InpFailMode
				Bit0No1Yes,
				hsw3000c01v1OperatingMode
				HswOperMode,
				hsw3000c01v1OperatingModeTrapEnable
				AlarmEnable,
				hsw3000c01v1StateAMap
				HswMapState,
				hsw3000c01v1StateBMap
				HswMapState,
				hsw3000c01v1StateAGpo
				HswGpoState,
				hsw3000c01v1StateBGpo
				HswGpoState,
				hsw3000c01v1AnaRefFmt
				SdiHd3gFmt5,
				hsw3000c01v1In1StChange
				Bit0No1Yes,
				hsw3000c01v1In2StChange
				Bit0No1Yes,
				hsw3000c01v1Gpi1StChange
				Bit0No1Yes,
				hsw3000c01v1Gpi2StChange
				Bit0No1Yes,
				hsw3000c01v1InputChange
				Bit0No1Yes,
				hsw3000c01v1VDelay
				DelayLines2,
				hsw3000c01v1HDelay
				DelayPixel5,
				hsw3000c01v1Holdoff
				TimeS2,
				hsw3000c01v1PhyFailTim
				HswTiming,
				hsw3000c01v1FmtFailTim
				HswTiming,
				hsw3000c01v1IncFailTim
				HswTiming,
				hsw3000c01v1GpiFailTim
				HswTiming,
				hsw3000c01v1BlkFailTim
				HswTiming,
				hsw3000c01v1FrzFailTim
				HswTiming,
				hsw3000c01v1PatFailTim
				HswTiming,
				hsw3000c01v1CrcFailTim
				HswTiming,
				hsw3000c01v1ActPer1
				TimeS2,
				hsw3000c01v1DeactPer1
				TimeS2,
				hsw3000c01v1ActPer2
				TimeS2,
				hsw3000c01v1DeactPer2
				TimeS2,
				hsw3000c01v1CrcThreshold
				Rate2,
				hsw3000c01v1BlackThreshold
				BlackThreshold,
				hsw3000c01v1VertFrozenWin
				Rate1,
				hsw3000c01v1HtalFrozenWin
				Rate1,
				hsw3000c01v1In1PhyFailMsk
				BitMask,
				hsw3000c01v1In1FmtFailMsk
				BitMask,
				hsw3000c01v1In1IncFailMsk
				BitMask,
				hsw3000c01v1In1GpiFailMsk
				BitMask,
				hsw3000c01v1In1BlkFailMsk
				BitMask,
				hsw3000c01v1In1FrzFailMsk
				BitMask,
				hsw3000c01v1In1PatFailMsk
				BitMask,
				hsw3000c01v1In1CrcFailMsk
				BitMask,
				hsw3000c01v1In2PhyFailMsk
				BitMask,
				hsw3000c01v1In2FmtFailMsk
				BitMask,
				hsw3000c01v1In2IncFailMsk
				BitMask,
				hsw3000c01v1In2GpiFailMsk
				BitMask,
				hsw3000c01v1In2BlkFailMsk
				BitMask,
				hsw3000c01v1In2FrzFailMsk
				BitMask,
				hsw3000c01v1In2PatFailMsk
				BitMask,
				hsw3000c01v1In2CrcFailMsk
				BitMask,
				hsw3000c01v1RefFailMsk
				BitMask,
				hsw3000c01v1LockFailMsk
				BitMask,
				hsw3000c01v1In1Fail
				BitFail,
				hsw3000c01v1In1FailTrapEnable
				AlarmEnable,
				hsw3000c01v1In2Fail
				BitFail,
				hsw3000c01v1In2FailTrapEnable
				AlarmEnable,
				hsw3000c01v1In1ExtFail
				BitFail,
				hsw3000c01v1In1ExtFailTrapEnable
				AlarmEnable,
				hsw3000c01v1In2ExtFail
				BitFail,
				hsw3000c01v1In2ExtFailTrapEnable
				AlarmEnable,
				hsw3000c01v1BlindExtFail
				BitFail,
				hsw3000c01v1BlindExtFailTrapEnable
				AlarmEnable,
				hsw3000c01v1SelOut1
				HswOutput,
				hsw3000c01v1SelOut1TrapEnable
				AlarmEnable,
				hsw3000c01v1SelOut2
				HswOutput,
				hsw3000c01v1SelOut2TrapEnable
				AlarmEnable,
				hsw3000c01v1Gpi3Stat
				BitFail,
				hsw3000c01v1Gpi3StatTrapEnable
				AlarmEnable,
				hsw3000c01v1In1PhyFail
				BitFail,
				hsw3000c01v1In1PhyFailTrapEnable
				AlarmEnable,
				hsw3000c01v1In1FmtFail
				BitFail,
				hsw3000c01v1In1FmtFailTrapEnable
				AlarmEnable,
				hsw3000c01v1In1IncFail
				BitFail,
				hsw3000c01v1In1IncFailTrapEnable
				AlarmEnable,
				hsw3000c01v1In1GpiFail
				BitFail,
				hsw3000c01v1In1GpiFailTrapEnable
				AlarmEnable,
				hsw3000c01v1In1BlkFail
				BitFail,
				hsw3000c01v1In1BlkFailTrapEnable
				AlarmEnable,
				hsw3000c01v1In1FrzFail
				BitFail,
				hsw3000c01v1In1FrzFailTrapEnable
				AlarmEnable,
				hsw3000c01v1In1PatFail
				BitFail,
				hsw3000c01v1In1PatFailTrapEnable
				AlarmEnable,
				hsw3000c01v1In1CrcFail
				BitFail,
				hsw3000c01v1In1CrcFailTrapEnable
				AlarmEnable,
				hsw3000c01v1In2PhyFail
				BitFail,
				hsw3000c01v1In2PhyFailTrapEnable
				AlarmEnable,
				hsw3000c01v1In2FmtFail
				BitFail,
				hsw3000c01v1In2FmtFailTrapEnable
				AlarmEnable,
				hsw3000c01v1In2IncFail
				BitFail,
				hsw3000c01v1In2IncFailTrapEnable
				AlarmEnable,
				hsw3000c01v1In2GpiFail
				BitFail,
				hsw3000c01v1In2GpiFailTrapEnable
				AlarmEnable,
				hsw3000c01v1In2BlkFail
				BitFail,
				hsw3000c01v1In2BlkFailTrapEnable
				AlarmEnable,
				hsw3000c01v1In2FrzFail
				BitFail,
				hsw3000c01v1In2FrzFailTrapEnable
				AlarmEnable,
				hsw3000c01v1In2PatFail
				BitFail,
				hsw3000c01v1In2PatFailTrapEnable
				AlarmEnable,
				hsw3000c01v1In2CrcFail
				BitFail,
				hsw3000c01v1In2CrcFailTrapEnable
				AlarmEnable,
				hsw3000c01v1RefFail
				BitFail,
				hsw3000c01v1RefFailTrapEnable
				AlarmEnable,
				hsw3000c01v1LockFail
				BitFail,
				hsw3000c01v1LockFailTrapEnable
				AlarmEnable,
				hsw3000c01v1BliGpiFail
				BitFail,
				hsw3000c01v1In1Format
				SdiHd3gFmt3,
				hsw3000c01v1In2Format
				SdiHd3gFmt3,
				hsw3000c01v1RefFormat
				SdiHd3gFmt3,
				hsw3000c01v1SerialNo
				SerialNo,
				hsw3000c01v1Gpi3StChange
				Bit0No1Yes
			 }

		-- 1.3.6.1.4.1.10106.3.101291.1.1.1
		hsw3000c01v1Index OBJECT-TYPE
			SYNTAX ModuleIndex
			MAX-ACCESS read-only
			STATUS current
			DESCRIPTION
				"Index of HSW3000C01V1 Table"
		::= { hsw3000c01v1Entry 1 }

		-- 1.3.6.1.4.1.10106.3.101291.1.1.3
		hsw3000c01v1ActivePreset OBJECT-TYPE
			SYNTAX PresetActive
			MAX-ACCESS read-only
			STATUS current
			DESCRIPTION
				"Shows the active preset"
		::= { hsw3000c01v1Entry 3 }

		-- 1.3.6.1.4.1.10106.3.101291.1.1.5
		hsw3000c01v1LoadPreset OBJECT-TYPE
			SYNTAX PresetLoad
			MAX-ACCESS read-write
			STATUS current
			DESCRIPTION
				"Allows loading a preset"
		::= { hsw3000c01v1Entry 5 }

		-- 1.3.6.1.4.1.10106.3.101291.1.1.7
		hsw3000c01v1SavePreset OBJECT-TYPE
			SYNTAX PresetSave
			MAX-ACCESS read-write
			STATUS current
			DESCRIPTION
				"Allows saving a preset"
		::= { hsw3000c01v1Entry 7 }

		-- 1.3.6.1.4.1.10106.3.101291.1.1.9
		hsw3000c01v1StateSel OBJECT-TYPE
			SYNTAX HswState
			MAX-ACCESS read-write
			STATUS current
			DESCRIPTION
				"Shows the module's current state"
		::= { hsw3000c01v1Entry 9 }

		-- 1.3.6.1.4.1.10106.3.101291.1.1.10
		hsw3000c01v1StateSelTrapEnable OBJECT-TYPE
			SYNTAX AlarmEnable
			MAX-ACCESS read-write
			STATUS current
			DESCRIPTION
				"Shows the module's current state Trap Enable"
		::= { hsw3000c01v1Entry 10 }

		-- 1.3.6.1.4.1.10106.3.101291.1.1.11
		hsw3000c01v1SwitchMode OBJECT-TYPE
			SYNTAX HswSwMode
			MAX-ACCESS read-write
			STATUS current
			DESCRIPTION
				"Allows selecting the switching mode"
		::= { hsw3000c01v1Entry 11 }

		-- 1.3.6.1.4.1.10106.3.101291.1.1.12
		hsw3000c01v1SwitchModeTrapEnable OBJECT-TYPE
			SYNTAX AlarmEnable
			MAX-ACCESS read-write
			STATUS current
			DESCRIPTION
				"Allows selecting the switching mode Trap Enable"
		::= { hsw3000c01v1Entry 12 }

		-- 1.3.6.1.4.1.10106.3.101291.1.1.13
		hsw3000c01v1FreezeMode OBJECT-TYPE
			SYNTAX HswFreezeMode
			MAX-ACCESS read-write
			STATUS current
			DESCRIPTION
				"Allows selecting the freeze detection mode"
		::= { hsw3000c01v1Entry 13 }

		-- 1.3.6.1.4.1.10106.3.101291.1.1.15
		hsw3000c01v1BypassEnable OBJECT-TYPE
			SYNTAX Bit0Dis1Ena
			MAX-ACCESS read-write
			STATUS current
			DESCRIPTION
				"Allows activating the rear board bypass"
		::= { hsw3000c01v1Entry 15 }

		-- 1.3.6.1.4.1.10106.3.101291.1.1.16
		hsw3000c01v1BypassEnableTrapEnable OBJECT-TYPE
			SYNTAX AlarmEnable
			MAX-ACCESS read-write
			STATUS current
			DESCRIPTION
				"Allows activating the rear board bypass Trap Enable"
		::= { hsw3000c01v1Entry 16 }

		-- 1.3.6.1.4.1.10106.3.101291.1.1.17
		hsw3000c01v1InpFailMode OBJECT-TYPE
			SYNTAX Bit0No1Yes
			MAX-ACCESS read-write
			STATUS current
			DESCRIPTION
				"Selects if the output is muted when the selected input fails"
		::= { hsw3000c01v1Entry 17 }

		-- 1.3.6.1.4.1.10106.3.101291.1.1.19
		hsw3000c01v1OperatingMode OBJECT-TYPE
			SYNTAX HswOperMode
			MAX-ACCESS read-write
			STATUS current
			DESCRIPTION
				"Allows selecting the operating mode"
		::= { hsw3000c01v1Entry 19 }

		-- 1.3.6.1.4.1.10106.3.101291.1.1.20
		hsw3000c01v1OperatingModeTrapEnable OBJECT-TYPE
			SYNTAX AlarmEnable
			MAX-ACCESS read-write
			STATUS current
			DESCRIPTION
				"Allows selecting the operating mode Trap Enable"
		::= { hsw3000c01v1Entry 20 }

		-- 1.3.6.1.4.1.10106.3.101291.1.1.21
		hsw3000c01v1StateAMap OBJECT-TYPE
			SYNTAX HswMapState
			MAX-ACCESS read-write
			STATUS current
			DESCRIPTION
				"Allow selecting the input to output mapping when state A is selected"
		::= { hsw3000c01v1Entry 21 }

		-- 1.3.6.1.4.1.10106.3.101291.1.1.23
		hsw3000c01v1StateBMap OBJECT-TYPE
			SYNTAX HswMapState
			MAX-ACCESS read-write
			STATUS current
			DESCRIPTION
				"Allow selecting the input to output mapping when state B is selected"
		::= { hsw3000c01v1Entry 23 }

		-- 1.3.6.1.4.1.10106.3.101291.1.1.25
		hsw3000c01v1StateAGpo OBJECT-TYPE
			SYNTAX HswGpoState
			MAX-ACCESS read-write
			STATUS current
			DESCRIPTION
				"Allow selecting the GPO configuration when state A is selected"
		::= { hsw3000c01v1Entry 25 }

		-- 1.3.6.1.4.1.10106.3.101291.1.1.27
		hsw3000c01v1StateBGpo OBJECT-TYPE
			SYNTAX HswGpoState
			MAX-ACCESS read-write
			STATUS current
			DESCRIPTION
				"Allow selecting the GPO configuration when state B is selected"
		::= { hsw3000c01v1Entry 27 }

		-- 1.3.6.1.4.1.10106.3.101291.1.1.29
		hsw3000c01v1AnaRefFmt OBJECT-TYPE
			SYNTAX SdiHd3gFmt5
			MAX-ACCESS read-write
			STATUS current
			DESCRIPTION
				"Analog reference input format"
		::= { hsw3000c01v1Entry 29 }

		-- 1.3.6.1.4.1.10106.3.101291.1.1.31
		hsw3000c01v1In1StChange OBJECT-TYPE
			SYNTAX Bit0No1Yes
			MAX-ACCESS read-write
			STATUS current
			DESCRIPTION
				"Signals a change in fail status"
		::= { hsw3000c01v1Entry 31 }

		-- 1.3.6.1.4.1.10106.3.101291.1.1.33
		hsw3000c01v1In2StChange OBJECT-TYPE
			SYNTAX Bit0No1Yes
			MAX-ACCESS read-write
			STATUS current
			DESCRIPTION
				"Signals a change in fail status"
		::= { hsw3000c01v1Entry 33 }

		-- 1.3.6.1.4.1.10106.3.101291.1.1.35
		hsw3000c01v1Gpi1StChange OBJECT-TYPE
			SYNTAX Bit0No1Yes
			MAX-ACCESS read-write
			STATUS current
			DESCRIPTION
				"Signals a change in GPI fail status"
		::= { hsw3000c01v1Entry 35 }

		-- 1.3.6.1.4.1.10106.3.101291.1.1.37
		hsw3000c01v1Gpi2StChange OBJECT-TYPE
			SYNTAX Bit0No1Yes
			MAX-ACCESS read-write
			STATUS current
			DESCRIPTION
				"Signals a change in GPI fail status"
		::= { hsw3000c01v1Entry 37 }

		-- 1.3.6.1.4.1.10106.3.101291.1.1.39
		hsw3000c01v1InputChange OBJECT-TYPE
			SYNTAX Bit0No1Yes
			MAX-ACCESS read-write
			STATUS current
			DESCRIPTION
				"Signals a change in selected input"
		::= { hsw3000c01v1Entry 39 }

		-- 1.3.6.1.4.1.10106.3.101291.1.1.41
		hsw3000c01v1VDelay OBJECT-TYPE
			SYNTAX DelayLines2
			MAX-ACCESS read-write
			STATUS current
			DESCRIPTION
				"Allows adjusting the video vertical delay"
		::= { hsw3000c01v1Entry 41 }

		-- 1.3.6.1.4.1.10106.3.101291.1.1.43
		hsw3000c01v1HDelay OBJECT-TYPE
			SYNTAX DelayPixel5
			MAX-ACCESS read-write
			STATUS current
			DESCRIPTION
				"Allows adjusting the video horizontal delay"
		::= { hsw3000c01v1Entry 43 }

		-- 1.3.6.1.4.1.10106.3.101291.1.1.45
		hsw3000c01v1Holdoff OBJECT-TYPE
			SYNTAX TimeS2
			MAX-ACCESS read-write
			STATUS current
			DESCRIPTION
				"Elapsed time after a switch event before a new switch occurs"
		::= { hsw3000c01v1Entry 45 }

		-- 1.3.6.1.4.1.10106.3.101291.1.1.47
		hsw3000c01v1PhyFailTim OBJECT-TYPE
			SYNTAX HswTiming
			MAX-ACCESS read-write
			STATUS current
			DESCRIPTION
				"Allows selecting the desired timing for the physical fail"
		::= { hsw3000c01v1Entry 47 }

		-- 1.3.6.1.4.1.10106.3.101291.1.1.49
		hsw3000c01v1FmtFailTim OBJECT-TYPE
			SYNTAX HswTiming
			MAX-ACCESS read-write
			STATUS current
			DESCRIPTION
				"Allows selecting the desired timing for the format fail"
		::= { hsw3000c01v1Entry 49 }

		-- 1.3.6.1.4.1.10106.3.101291.1.1.51
		hsw3000c01v1IncFailTim OBJECT-TYPE
			SYNTAX HswTiming
			MAX-ACCESS read-write
			STATUS current
			DESCRIPTION
				"Allows selecting the desired timing for the incompatible format fail"
		::= { hsw3000c01v1Entry 51 }

		-- 1.3.6.1.4.1.10106.3.101291.1.1.53
		hsw3000c01v1GpiFailTim OBJECT-TYPE
			SYNTAX HswTiming
			MAX-ACCESS read-write
			STATUS current
			DESCRIPTION
				"Allows selecting the desired timing for the GPI fail"
		::= { hsw3000c01v1Entry 53 }

		-- 1.3.6.1.4.1.10106.3.101291.1.1.55
		hsw3000c01v1BlkFailTim OBJECT-TYPE
			SYNTAX HswTiming
			MAX-ACCESS read-write
			STATUS current
			DESCRIPTION
				"Allows selecting the desired timing for the black fail"
		::= { hsw3000c01v1Entry 55 }

		-- 1.3.6.1.4.1.10106.3.101291.1.1.57
		hsw3000c01v1FrzFailTim OBJECT-TYPE
			SYNTAX HswTiming
			MAX-ACCESS read-write
			STATUS current
			DESCRIPTION
				"Allows selecting the desired timing for the freeze fail"
		::= { hsw3000c01v1Entry 57 }

		-- 1.3.6.1.4.1.10106.3.101291.1.1.59
		hsw3000c01v1PatFailTim OBJECT-TYPE
			SYNTAX HswTiming
			MAX-ACCESS read-write
			STATUS current
			DESCRIPTION
				"Allows selecting the desired timing for the pattern fail"
		::= { hsw3000c01v1Entry 59 }

		-- 1.3.6.1.4.1.10106.3.101291.1.1.61
		hsw3000c01v1CrcFailTim OBJECT-TYPE
			SYNTAX HswTiming
			MAX-ACCESS read-write
			STATUS current
			DESCRIPTION
				"Allows selecting the desired timing for the EDH/CRC"
		::= { hsw3000c01v1Entry 61 }

		-- 1.3.6.1.4.1.10106.3.101291.1.1.63
		hsw3000c01v1ActPer1 OBJECT-TYPE
			SYNTAX TimeS2
			MAX-ACCESS read-write
			STATUS current
			DESCRIPTION
				"Activation time used in timing 1"
		::= { hsw3000c01v1Entry 63 }

		-- 1.3.6.1.4.1.10106.3.101291.1.1.65
		hsw3000c01v1DeactPer1 OBJECT-TYPE
			SYNTAX TimeS2
			MAX-ACCESS read-write
			STATUS current
			DESCRIPTION
				"Deactivation time used in timing 1"
		::= { hsw3000c01v1Entry 65 }

		-- 1.3.6.1.4.1.10106.3.101291.1.1.67
		hsw3000c01v1ActPer2 OBJECT-TYPE
			SYNTAX TimeS2
			MAX-ACCESS read-write
			STATUS current
			DESCRIPTION
				"Activation time used in timing 2"
		::= { hsw3000c01v1Entry 67 }

		-- 1.3.6.1.4.1.10106.3.101291.1.1.69
		hsw3000c01v1DeactPer2 OBJECT-TYPE
			SYNTAX TimeS2
			MAX-ACCESS read-write
			STATUS current
			DESCRIPTION
				"Deactivation time used in timing 2"
		::= { hsw3000c01v1Entry 69 }

		-- 1.3.6.1.4.1.10106.3.101291.1.1.71
		hsw3000c01v1CrcThreshold OBJECT-TYPE
			SYNTAX Rate2
			MAX-ACCESS read-write
			STATUS current
			DESCRIPTION
				"Allows adjusting the threshold that activates the EDH/CRC fail"
		::= { hsw3000c01v1Entry 71 }

		-- 1.3.6.1.4.1.10106.3.101291.1.1.73
		hsw3000c01v1BlackThreshold OBJECT-TYPE
			SYNTAX BlackThreshold
			MAX-ACCESS read-write
			STATUS current
			DESCRIPTION
				"Allows adjusting the threshold thas activates the black fail"
		::= { hsw3000c01v1Entry 73 }

		-- 1.3.6.1.4.1.10106.3.101291.1.1.75
		hsw3000c01v1VertFrozenWin OBJECT-TYPE
			SYNTAX Rate1
			MAX-ACCESS read-write
			STATUS current
			DESCRIPTION
				"Allows adjusting the vertical size of the window used in the freeze detector"
		::= { hsw3000c01v1Entry 75 }

		-- 1.3.6.1.4.1.10106.3.101291.1.1.77
		hsw3000c01v1HtalFrozenWin OBJECT-TYPE
			SYNTAX Rate1
			MAX-ACCESS read-write
			STATUS current
			DESCRIPTION
				"Allows adjusting the horizontal size of the window used in the freeze detector"
		::= { hsw3000c01v1Entry 77 }

		-- 1.3.6.1.4.1.10106.3.101291.1.1.79
		hsw3000c01v1In1PhyFailMsk OBJECT-TYPE
			SYNTAX BitMask
			MAX-ACCESS read-write
			STATUS current
			DESCRIPTION
				"Allows masking the signal absence fail"
		::= { hsw3000c01v1Entry 79 }

		-- 1.3.6.1.4.1.10106.3.101291.1.1.81
		hsw3000c01v1In1FmtFailMsk OBJECT-TYPE
			SYNTAX BitMask
			MAX-ACCESS read-write
			STATUS current
			DESCRIPTION
				"Allows masking the format fail"
		::= { hsw3000c01v1Entry 81 }

		-- 1.3.6.1.4.1.10106.3.101291.1.1.83
		hsw3000c01v1In1IncFailMsk OBJECT-TYPE
			SYNTAX BitMask
			MAX-ACCESS read-write
			STATUS current
			DESCRIPTION
				"Allows masking the incompatible format fail"
		::= { hsw3000c01v1Entry 83 }

		-- 1.3.6.1.4.1.10106.3.101291.1.1.85
		hsw3000c01v1In1GpiFailMsk OBJECT-TYPE
			SYNTAX BitMask
			MAX-ACCESS read-write
			STATUS current
			DESCRIPTION
				"Allows masking the GPI fail"
		::= { hsw3000c01v1Entry 85 }

		-- 1.3.6.1.4.1.10106.3.101291.1.1.87
		hsw3000c01v1In1BlkFailMsk OBJECT-TYPE
			SYNTAX BitMask
			MAX-ACCESS read-write
			STATUS current
			DESCRIPTION
				"Allows masking the black signal fail"
		::= { hsw3000c01v1Entry 87 }

		-- 1.3.6.1.4.1.10106.3.101291.1.1.89
		hsw3000c01v1In1FrzFailMsk OBJECT-TYPE
			SYNTAX BitMask
			MAX-ACCESS read-write
			STATUS current
			DESCRIPTION
				"Allows masking the freeze signal fail"
		::= { hsw3000c01v1Entry 89 }

		-- 1.3.6.1.4.1.10106.3.101291.1.1.91
		hsw3000c01v1In1PatFailMsk OBJECT-TYPE
			SYNTAX BitMask
			MAX-ACCESS read-write
			STATUS current
			DESCRIPTION
				"Allows masking the video pattern fail"
		::= { hsw3000c01v1Entry 91 }

		-- 1.3.6.1.4.1.10106.3.101291.1.1.93
		hsw3000c01v1In1CrcFailMsk OBJECT-TYPE
			SYNTAX BitMask
			MAX-ACCESS read-write
			STATUS current
			DESCRIPTION
				"Allows masking the EDH/CRC"
		::= { hsw3000c01v1Entry 93 }

		-- 1.3.6.1.4.1.10106.3.101291.1.1.95
		hsw3000c01v1In2PhyFailMsk OBJECT-TYPE
			SYNTAX BitMask
			MAX-ACCESS read-write
			STATUS current
			DESCRIPTION
				"Allows masking the signal absence fail"
		::= { hsw3000c01v1Entry 95 }

		-- 1.3.6.1.4.1.10106.3.101291.1.1.97
		hsw3000c01v1In2FmtFailMsk OBJECT-TYPE
			SYNTAX BitMask
			MAX-ACCESS read-write
			STATUS current
			DESCRIPTION
				"Allows masking the format fail"
		::= { hsw3000c01v1Entry 97 }

		-- 1.3.6.1.4.1.10106.3.101291.1.1.99
		hsw3000c01v1In2IncFailMsk OBJECT-TYPE
			SYNTAX BitMask
			MAX-ACCESS read-write
			STATUS current
			DESCRIPTION
				"Allows masking the incompatible format fail"
		::= { hsw3000c01v1Entry 99 }

		-- 1.3.6.1.4.1.10106.3.101291.1.1.101
		hsw3000c01v1In2GpiFailMsk OBJECT-TYPE
			SYNTAX BitMask
			MAX-ACCESS read-write
			STATUS current
			DESCRIPTION
				"Allows masking the GPI fail"
		::= { hsw3000c01v1Entry 101 }

		-- 1.3.6.1.4.1.10106.3.101291.1.1.103
		hsw3000c01v1In2BlkFailMsk OBJECT-TYPE
			SYNTAX BitMask
			MAX-ACCESS read-write
			STATUS current
			DESCRIPTION
				"Allows masking the black signal fail"
		::= { hsw3000c01v1Entry 103 }

		-- 1.3.6.1.4.1.10106.3.101291.1.1.105
		hsw3000c01v1In2FrzFailMsk OBJECT-TYPE
			SYNTAX BitMask
			MAX-ACCESS read-write
			STATUS current
			DESCRIPTION
				"Allows masking the freeze signal fail"
		::= { hsw3000c01v1Entry 105 }

		-- 1.3.6.1.4.1.10106.3.101291.1.1.107
		hsw3000c01v1In2PatFailMsk OBJECT-TYPE
			SYNTAX BitMask
			MAX-ACCESS read-write
			STATUS current
			DESCRIPTION
				"Allows masking the video pattern fail"
		::= { hsw3000c01v1Entry 107 }

		-- 1.3.6.1.4.1.10106.3.101291.1.1.109
		hsw3000c01v1In2CrcFailMsk OBJECT-TYPE
			SYNTAX BitMask
			MAX-ACCESS read-write
			STATUS current
			DESCRIPTION
				"Allows masking the EDH/CRC"
		::= { hsw3000c01v1Entry 109 }

		-- 1.3.6.1.4.1.10106.3.101291.1.1.111
		hsw3000c01v1RefFailMsk OBJECT-TYPE
			SYNTAX BitMask
			MAX-ACCESS read-write
			STATUS current
			DESCRIPTION
				"Allows masking the reference absence fail"
		::= { hsw3000c01v1Entry 111 }

		-- 1.3.6.1.4.1.10106.3.101291.1.1.113
		hsw3000c01v1LockFailMsk OBJECT-TYPE
			SYNTAX BitMask
			MAX-ACCESS read-write
			STATUS current
			DESCRIPTION
				"Allows masking the reference unlock fail"
		::= { hsw3000c01v1Entry 113 }

		-- 1.3.6.1.4.1.10106.3.101291.1.1.115
		hsw3000c01v1In1Fail OBJECT-TYPE
			SYNTAX BitFail
			MAX-ACCESS read-only
			STATUS current
			DESCRIPTION
				"Input 1 fail"
		::= { hsw3000c01v1Entry 115 }

		-- 1.3.6.1.4.1.10106.3.101291.1.1.116
		hsw3000c01v1In1FailTrapEnable OBJECT-TYPE
			SYNTAX AlarmEnable
			MAX-ACCESS read-write
			STATUS current
			DESCRIPTION
				"Input 1 fail Trap Enable"
		::= { hsw3000c01v1Entry 116 }

		-- 1.3.6.1.4.1.10106.3.101291.1.1.117
		hsw3000c01v1In2Fail OBJECT-TYPE
			SYNTAX BitFail
			MAX-ACCESS read-only
			STATUS current
			DESCRIPTION
				"Input 2 fail"
		::= { hsw3000c01v1Entry 117 }

		-- 1.3.6.1.4.1.10106.3.101291.1.1.118
		hsw3000c01v1In2FailTrapEnable OBJECT-TYPE
			SYNTAX AlarmEnable
			MAX-ACCESS read-write
			STATUS current
			DESCRIPTION
				"Input 2 fail Trap Enable"
		::= { hsw3000c01v1Entry 118 }

		-- 1.3.6.1.4.1.10106.3.101291.1.1.119
		hsw3000c01v1In1ExtFail OBJECT-TYPE
			SYNTAX BitFail
			MAX-ACCESS read-only
			STATUS current
			DESCRIPTION
				"Input 1 GPI fail (GPI1A)"
		::= { hsw3000c01v1Entry 119 }

		-- 1.3.6.1.4.1.10106.3.101291.1.1.120
		hsw3000c01v1In1ExtFailTrapEnable OBJECT-TYPE
			SYNTAX AlarmEnable
			MAX-ACCESS read-write
			STATUS current
			DESCRIPTION
				"Input 1 GPI fail (GPI1A) Trap Enable"
		::= { hsw3000c01v1Entry 120 }

		-- 1.3.6.1.4.1.10106.3.101291.1.1.121
		hsw3000c01v1In2ExtFail OBJECT-TYPE
			SYNTAX BitFail
			MAX-ACCESS read-only
			STATUS current
			DESCRIPTION
				"Input 2 GPI fail (GPI2A)"
		::= { hsw3000c01v1Entry 121 }

		-- 1.3.6.1.4.1.10106.3.101291.1.1.122
		hsw3000c01v1In2ExtFailTrapEnable OBJECT-TYPE
			SYNTAX AlarmEnable
			MAX-ACCESS read-write
			STATUS current
			DESCRIPTION
				"Input 2 GPI fail (GPI2A) Trap Enable"
		::= { hsw3000c01v1Entry 122 }

		-- 1.3.6.1.4.1.10106.3.101291.1.1.123
		hsw3000c01v1BlindExtFail OBJECT-TYPE
			SYNTAX BitFail
			MAX-ACCESS read-only
			STATUS current
			DESCRIPTION
				"Blind halfauto control GPI fail (GPI2B)"
		::= { hsw3000c01v1Entry 123 }

		-- 1.3.6.1.4.1.10106.3.101291.1.1.124
		hsw3000c01v1BlindExtFailTrapEnable OBJECT-TYPE
			SYNTAX AlarmEnable
			MAX-ACCESS read-write
			STATUS current
			DESCRIPTION
				"Blind halfauto control GPI fail (GPI2B) Trap Enable"
		::= { hsw3000c01v1Entry 124 }

		-- 1.3.6.1.4.1.10106.3.101291.1.1.125
		hsw3000c01v1SelOut1 OBJECT-TYPE
			SYNTAX HswOutput
			MAX-ACCESS read-only
			STATUS current
			DESCRIPTION
				"Output 1"
		::= { hsw3000c01v1Entry 125 }

		-- 1.3.6.1.4.1.10106.3.101291.1.1.126
		hsw3000c01v1SelOut1TrapEnable OBJECT-TYPE
			SYNTAX AlarmEnable
			MAX-ACCESS read-write
			STATUS current
			DESCRIPTION
				"Output 1 Trap Enable"
		::= { hsw3000c01v1Entry 126 }

		-- 1.3.6.1.4.1.10106.3.101291.1.1.127
		hsw3000c01v1SelOut2 OBJECT-TYPE
			SYNTAX HswOutput
			MAX-ACCESS read-only
			STATUS current
			DESCRIPTION
				"Output 2"
		::= { hsw3000c01v1Entry 127 }

		-- 1.3.6.1.4.1.10106.3.101291.1.1.128
		hsw3000c01v1SelOut2TrapEnable OBJECT-TYPE
			SYNTAX AlarmEnable
			MAX-ACCESS read-write
			STATUS current
			DESCRIPTION
				"Output 2 Trap Enable"
		::= { hsw3000c01v1Entry 128 }

		-- 1.3.6.1.4.1.10106.3.101291.1.1.129
		hsw3000c01v1Gpi3Stat OBJECT-TYPE
			SYNTAX BitFail
			MAX-ACCESS read-only
			STATUS current
			DESCRIPTION
				"GPI1B status (used in remote control)"
		::= { hsw3000c01v1Entry 129 }

		-- 1.3.6.1.4.1.10106.3.101291.1.1.130
		hsw3000c01v1Gpi3StatTrapEnable OBJECT-TYPE
			SYNTAX AlarmEnable
			MAX-ACCESS read-write
			STATUS current
			DESCRIPTION
				"GPI1B status (used in remote control) Trap Enable"
		::= { hsw3000c01v1Entry 130 }

		-- 1.3.6.1.4.1.10106.3.101291.1.1.131
		hsw3000c01v1In1PhyFail OBJECT-TYPE
			SYNTAX BitFail
			MAX-ACCESS read-only
			STATUS current
			DESCRIPTION
				"Absence fail"
		::= { hsw3000c01v1Entry 131 }

		-- 1.3.6.1.4.1.10106.3.101291.1.1.132
		hsw3000c01v1In1PhyFailTrapEnable OBJECT-TYPE
			SYNTAX AlarmEnable
			MAX-ACCESS read-write
			STATUS current
			DESCRIPTION
				"Absence fail Trap Enable"
		::= { hsw3000c01v1Entry 132 }

		-- 1.3.6.1.4.1.10106.3.101291.1.1.133
		hsw3000c01v1In1FmtFail OBJECT-TYPE
			SYNTAX BitFail
			MAX-ACCESS read-only
			STATUS current
			DESCRIPTION
				"Format fail"
		::= { hsw3000c01v1Entry 133 }

		-- 1.3.6.1.4.1.10106.3.101291.1.1.134
		hsw3000c01v1In1FmtFailTrapEnable OBJECT-TYPE
			SYNTAX AlarmEnable
			MAX-ACCESS read-write
			STATUS current
			DESCRIPTION
				"Format fail Trap Enable"
		::= { hsw3000c01v1Entry 134 }

		-- 1.3.6.1.4.1.10106.3.101291.1.1.135
		hsw3000c01v1In1IncFail OBJECT-TYPE
			SYNTAX BitFail
			MAX-ACCESS read-only
			STATUS current
			DESCRIPTION
				"Incompatible format fail"
		::= { hsw3000c01v1Entry 135 }

		-- 1.3.6.1.4.1.10106.3.101291.1.1.136
		hsw3000c01v1In1IncFailTrapEnable OBJECT-TYPE
			SYNTAX AlarmEnable
			MAX-ACCESS read-write
			STATUS current
			DESCRIPTION
				"Incompatible format fail Trap Enable"
		::= { hsw3000c01v1Entry 136 }

		-- 1.3.6.1.4.1.10106.3.101291.1.1.137
		hsw3000c01v1In1GpiFail OBJECT-TYPE
			SYNTAX BitFail
			MAX-ACCESS read-only
			STATUS current
			DESCRIPTION
				"External GPI fail"
		::= { hsw3000c01v1Entry 137 }

		-- 1.3.6.1.4.1.10106.3.101291.1.1.138
		hsw3000c01v1In1GpiFailTrapEnable OBJECT-TYPE
			SYNTAX AlarmEnable
			MAX-ACCESS read-write
			STATUS current
			DESCRIPTION
				"External GPI fail Trap Enable"
		::= { hsw3000c01v1Entry 138 }

		-- 1.3.6.1.4.1.10106.3.101291.1.1.139
		hsw3000c01v1In1BlkFail OBJECT-TYPE
			SYNTAX BitFail
			MAX-ACCESS read-only
			STATUS current
			DESCRIPTION
				"Black signal fail"
		::= { hsw3000c01v1Entry 139 }

		-- 1.3.6.1.4.1.10106.3.101291.1.1.140
		hsw3000c01v1In1BlkFailTrapEnable OBJECT-TYPE
			SYNTAX AlarmEnable
			MAX-ACCESS read-write
			STATUS current
			DESCRIPTION
				"Black signal fail Trap Enable"
		::= { hsw3000c01v1Entry 140 }

		-- 1.3.6.1.4.1.10106.3.101291.1.1.141
		hsw3000c01v1In1FrzFail OBJECT-TYPE
			SYNTAX BitFail
			MAX-ACCESS read-only
			STATUS current
			DESCRIPTION
				"Freeze signal fail"
		::= { hsw3000c01v1Entry 141 }

		-- 1.3.6.1.4.1.10106.3.101291.1.1.142
		hsw3000c01v1In1FrzFailTrapEnable OBJECT-TYPE
			SYNTAX AlarmEnable
			MAX-ACCESS read-write
			STATUS current
			DESCRIPTION
				"Freeze signal fail Trap Enable"
		::= { hsw3000c01v1Entry 142 }

		-- 1.3.6.1.4.1.10106.3.101291.1.1.143
		hsw3000c01v1In1PatFail OBJECT-TYPE
			SYNTAX BitFail
			MAX-ACCESS read-only
			STATUS current
			DESCRIPTION
				"Video pattern fail"
		::= { hsw3000c01v1Entry 143 }

		-- 1.3.6.1.4.1.10106.3.101291.1.1.144
		hsw3000c01v1In1PatFailTrapEnable OBJECT-TYPE
			SYNTAX AlarmEnable
			MAX-ACCESS read-write
			STATUS current
			DESCRIPTION
				"Video pattern fail Trap Enable"
		::= { hsw3000c01v1Entry 144 }

		-- 1.3.6.1.4.1.10106.3.101291.1.1.145
		hsw3000c01v1In1CrcFail OBJECT-TYPE
			SYNTAX BitFail
			MAX-ACCESS read-only
			STATUS current
			DESCRIPTION
				"EDH/CRC fail"
		::= { hsw3000c01v1Entry 145 }

		-- 1.3.6.1.4.1.10106.3.101291.1.1.146
		hsw3000c01v1In1CrcFailTrapEnable OBJECT-TYPE
			SYNTAX AlarmEnable
			MAX-ACCESS read-write
			STATUS current
			DESCRIPTION
				"EDH/CRC fail Trap Enable"
		::= { hsw3000c01v1Entry 146 }

		-- 1.3.6.1.4.1.10106.3.101291.1.1.147
		hsw3000c01v1In2PhyFail OBJECT-TYPE
			SYNTAX BitFail
			MAX-ACCESS read-only
			STATUS current
			DESCRIPTION
				"Absence fail"
		::= { hsw3000c01v1Entry 147 }

		-- 1.3.6.1.4.1.10106.3.101291.1.1.148
		hsw3000c01v1In2PhyFailTrapEnable OBJECT-TYPE
			SYNTAX AlarmEnable
			MAX-ACCESS read-write
			STATUS current
			DESCRIPTION
				"Absence fail Trap Enable"
		::= { hsw3000c01v1Entry 148 }

		-- 1.3.6.1.4.1.10106.3.101291.1.1.149
		hsw3000c01v1In2FmtFail OBJECT-TYPE
			SYNTAX BitFail
			MAX-ACCESS read-only
			STATUS current
			DESCRIPTION
				"Format fail"
		::= { hsw3000c01v1Entry 149 }

		-- 1.3.6.1.4.1.10106.3.101291.1.1.150
		hsw3000c01v1In2FmtFailTrapEnable OBJECT-TYPE
			SYNTAX AlarmEnable
			MAX-ACCESS read-write
			STATUS current
			DESCRIPTION
				"Format fail Trap Enable"
		::= { hsw3000c01v1Entry 150 }

		-- 1.3.6.1.4.1.10106.3.101291.1.1.151
		hsw3000c01v1In2IncFail OBJECT-TYPE
			SYNTAX BitFail
			MAX-ACCESS read-only
			STATUS current
			DESCRIPTION
				"Incompatible format fail"
		::= { hsw3000c01v1Entry 151 }

		-- 1.3.6.1.4.1.10106.3.101291.1.1.152
		hsw3000c01v1In2IncFailTrapEnable OBJECT-TYPE
			SYNTAX AlarmEnable
			MAX-ACCESS read-write
			STATUS current
			DESCRIPTION
				"Incompatible format fail Trap Enable"
		::= { hsw3000c01v1Entry 152 }

		-- 1.3.6.1.4.1.10106.3.101291.1.1.153
		hsw3000c01v1In2GpiFail OBJECT-TYPE
			SYNTAX BitFail
			MAX-ACCESS read-only
			STATUS current
			DESCRIPTION
				"External GPI fail"
		::= { hsw3000c01v1Entry 153 }

		-- 1.3.6.1.4.1.10106.3.101291.1.1.154
		hsw3000c01v1In2GpiFailTrapEnable OBJECT-TYPE
			SYNTAX AlarmEnable
			MAX-ACCESS read-write
			STATUS current
			DESCRIPTION
				"External GPI fail Trap Enable"
		::= { hsw3000c01v1Entry 154 }

		-- 1.3.6.1.4.1.10106.3.101291.1.1.155
		hsw3000c01v1In2BlkFail OBJECT-TYPE
			SYNTAX BitFail
			MAX-ACCESS read-only
			STATUS current
			DESCRIPTION
				"Black signal fail"
		::= { hsw3000c01v1Entry 155 }

		-- 1.3.6.1.4.1.10106.3.101291.1.1.156
		hsw3000c01v1In2BlkFailTrapEnable OBJECT-TYPE
			SYNTAX AlarmEnable
			MAX-ACCESS read-write
			STATUS current
			DESCRIPTION
				"Black signal fail Trap Enable"
		::= { hsw3000c01v1Entry 156 }

		-- 1.3.6.1.4.1.10106.3.101291.1.1.157
		hsw3000c01v1In2FrzFail OBJECT-TYPE
			SYNTAX BitFail
			MAX-ACCESS read-only
			STATUS current
			DESCRIPTION
				"Freeze signal fail"
		::= { hsw3000c01v1Entry 157 }

		-- 1.3.6.1.4.1.10106.3.101291.1.1.158
		hsw3000c01v1In2FrzFailTrapEnable OBJECT-TYPE
			SYNTAX AlarmEnable
			MAX-ACCESS read-write
			STATUS current
			DESCRIPTION
				"Freeze signal fail Trap Enable"
		::= { hsw3000c01v1Entry 158 }

		-- 1.3.6.1.4.1.10106.3.101291.1.1.159
		hsw3000c01v1In2PatFail OBJECT-TYPE
			SYNTAX BitFail
			MAX-ACCESS read-only
			STATUS current
			DESCRIPTION
				"Video pattern fail"
		::= { hsw3000c01v1Entry 159 }

		-- 1.3.6.1.4.1.10106.3.101291.1.1.160
		hsw3000c01v1In2PatFailTrapEnable OBJECT-TYPE
			SYNTAX AlarmEnable
			MAX-ACCESS read-write
			STATUS current
			DESCRIPTION
				"Video pattern fail Trap Enable"
		::= { hsw3000c01v1Entry 160 }

		-- 1.3.6.1.4.1.10106.3.101291.1.1.161
		hsw3000c01v1In2CrcFail OBJECT-TYPE
			SYNTAX BitFail
			MAX-ACCESS read-only
			STATUS current
			DESCRIPTION
				"EDH/CRC fail"
		::= { hsw3000c01v1Entry 161 }

		-- 1.3.6.1.4.1.10106.3.101291.1.1.162
		hsw3000c01v1In2CrcFailTrapEnable OBJECT-TYPE
			SYNTAX AlarmEnable
			MAX-ACCESS read-write
			STATUS current
			DESCRIPTION
				"EDH/CRC fail Trap Enable"
		::= { hsw3000c01v1Entry 162 }

		-- 1.3.6.1.4.1.10106.3.101291.1.1.163
		hsw3000c01v1RefFail OBJECT-TYPE
			SYNTAX BitFail
			MAX-ACCESS read-only
			STATUS current
			DESCRIPTION
				"Reference absence fail"
		::= { hsw3000c01v1Entry 163 }

		-- 1.3.6.1.4.1.10106.3.101291.1.1.164
		hsw3000c01v1RefFailTrapEnable OBJECT-TYPE
			SYNTAX AlarmEnable
			MAX-ACCESS read-write
			STATUS current
			DESCRIPTION
				"Reference absence fail Trap Enable"
		::= { hsw3000c01v1Entry 164 }

		-- 1.3.6.1.4.1.10106.3.101291.1.1.165
		hsw3000c01v1LockFail OBJECT-TYPE
			SYNTAX BitFail
			MAX-ACCESS read-only
			STATUS current
			DESCRIPTION
				"Reference unlock fail"
		::= { hsw3000c01v1Entry 165 }

		-- 1.3.6.1.4.1.10106.3.101291.1.1.166
		hsw3000c01v1LockFailTrapEnable OBJECT-TYPE
			SYNTAX AlarmEnable
			MAX-ACCESS read-write
			STATUS current
			DESCRIPTION
				"Reference unlock fail Trap Enable"
		::= { hsw3000c01v1Entry 166 }

		-- 1.3.6.1.4.1.10106.3.101291.1.1.167
		hsw3000c01v1BliGpiFail OBJECT-TYPE
			SYNTAX BitFail
			MAX-ACCESS read-only
			STATUS current
			DESCRIPTION
				"GPI2B status (used in blind halfauto mode)"
		::= { hsw3000c01v1Entry 167 }

		-- 1.3.6.1.4.1.10106.3.101291.1.1.169
		hsw3000c01v1In1Format OBJECT-TYPE
			SYNTAX SdiHd3gFmt3
			MAX-ACCESS read-only
			STATUS current
			DESCRIPTION
				"Input format"
		::= { hsw3000c01v1Entry 169 }

		-- 1.3.6.1.4.1.10106.3.101291.1.1.171
		hsw3000c01v1In2Format OBJECT-TYPE
			SYNTAX SdiHd3gFmt3
			MAX-ACCESS read-only
			STATUS current
			DESCRIPTION
				"Input format"
		::= { hsw3000c01v1Entry 171 }

		-- 1.3.6.1.4.1.10106.3.101291.1.1.173
		hsw3000c01v1RefFormat OBJECT-TYPE
			SYNTAX SdiHd3gFmt3
			MAX-ACCESS read-only
			STATUS current
			DESCRIPTION
				"Reference format"
		::= { hsw3000c01v1Entry 173 }

		-- 1.3.6.1.4.1.10106.3.101291.1.1.175
		hsw3000c01v1SerialNo OBJECT-TYPE
			SYNTAX SerialNo
			MAX-ACCESS read-only
			STATUS current
			DESCRIPTION
				"Serial number"
		::= { hsw3000c01v1Entry 175 }

		-- 1.3.6.1.4.1.10106.3.101291.1.1.177
		hsw3000c01v1Gpi3StChange OBJECT-TYPE
			SYNTAX Bit0No1Yes
			MAX-ACCESS read-write
			STATUS current
			DESCRIPTION
				"Signals a change in GPI fail status (GPI2B)"
		::= { hsw3000c01v1Entry 177 }

		-- 1.3.6.1.4.1.10106.3.364802
		hsw3000c01v2 OBJECT IDENTIFIER ::= { albalaProducts 364802 }

		-- 1.3.6.1.4.1.10106.3.364802.1
		hsw3000c01v2Table  OBJECT-TYPE
			SYNTAX SEQUENCE OF Hsw3000c01v2Entry
			MAX-ACCESS not-accessible
			STATUS current
			DESCRIPTION
				"Module  HSW3000C01V2 Table"
			::= { hsw3000c01v2 1 }

		-- 1.3.6.1.4.1.10106.3.364802.1.1
		hsw3000c01v2Entry  OBJECT-TYPE
			SYNTAX Hsw3000c01v2Entry
			MAX-ACCESS not-accessible
			STATUS current
			DESCRIPTION
				"Module HSW3000C01V2 Entry"
			INDEX { hsw3000c01v2Index }
			::= { hsw3000c01v2Table 1 }

			Hsw3000c01v2Entry ::=
			SEQUENCE {
				hsw3000c01v2Index
				ModuleIndex,
				hsw3000c01v2ActivePreset
				PresetActive,
				hsw3000c01v2LoadPreset
				PresetLoad,
				hsw3000c01v2SavePreset
				PresetSave,
				hsw3000c01v2StateSel
				HswState,
				hsw3000c01v2StateSelTrapEnable
				AlarmEnable,
				hsw3000c01v2SwitchMode
				HswSwMode,
				hsw3000c01v2SwitchModeTrapEnable
				AlarmEnable,
				hsw3000c01v2FreezeMode
				HswFreezeMode,
				hsw3000c01v2BypassEnable
				Bit0Dis1Ena,
				hsw3000c01v2BypassEnableTrapEnable
				AlarmEnable,
				hsw3000c01v2InpFailMode
				Bit0No1Yes,
				hsw3000c01v2OperatingMode
				HswOperMode,
				hsw3000c01v2OperatingModeTrapEnable
				AlarmEnable,
				hsw3000c01v2StateAMap
				HswMapState,
				hsw3000c01v2StateBMap
				HswMapState,
				hsw3000c01v2StateAGpo
				HswGpoState,
				hsw3000c01v2StateBGpo
				HswGpoState,
				hsw3000c01v2AnaRefFmt
				SdiHd3gFmt5,
				hsw3000c01v2In1StChange
				Bit0No1Yes,
				hsw3000c01v2In2StChange
				Bit0No1Yes,
				hsw3000c01v2Gpi1StChange
				Bit0No1Yes,
				hsw3000c01v2Gpi2StChange
				Bit0No1Yes,
				hsw3000c01v2Gpi3StChange
				Bit0No1Yes,
				hsw3000c01v2InputChange
				Bit0No1Yes,
				hsw3000c01v2VDelay
				DelayLines2,
				hsw3000c01v2HDelay
				DelayPixel5,
				hsw3000c01v2Holdoff
				TimeS2,
				hsw3000c01v2PhyFailTim
				HswTiming,
				hsw3000c01v2FmtFailTim
				HswTiming,
				hsw3000c01v2IncFailTim
				HswTiming,
				hsw3000c01v2GpiFailTim
				HswTiming,
				hsw3000c01v2BlkFailTim
				HswTiming,
				hsw3000c01v2FrzFailTim
				HswTiming,
				hsw3000c01v2PatFailTim
				HswTiming,
				hsw3000c01v2CrcFailTim
				HswTiming,
				hsw3000c01v2SilFailTim
				HswTiming,
				hsw3000c01v2OvrFailTim
				HswTiming,
				hsw3000c01v2PhFailTim
				HswTiming,
				hsw3000c01v2PresFailTim
				HswTiming,
				hsw3000c01v2ActPer1
				TimeS2,
				hsw3000c01v2DeactPer1
				TimeS2,
				hsw3000c01v2ActPer2
				TimeS2,
				hsw3000c01v2DeactPer2
				TimeS2,
				hsw3000c01v2CrcThreshold
				Rate2,
				hsw3000c01v2BlackThreshold
				BlackThreshold,
				hsw3000c01v2VertFrozenWin
				Rate1,
				hsw3000c01v2HtalFrozenWin
				Rate1,
				hsw3000c01v2In1PhyFailMsk
				BitMask,
				hsw3000c01v2In1FmtFailMsk
				BitMask,
				hsw3000c01v2In1IncFailMsk
				BitMask,
				hsw3000c01v2In1GpiFailMsk
				BitMask,
				hsw3000c01v2In1BlkFailMsk
				BitMask,
				hsw3000c01v2In1FrzFailMsk
				BitMask,
				hsw3000c01v2In1PatFailMsk
				BitMask,
				hsw3000c01v2In1CrcFailMsk
				BitMask,
				hsw3000c01v2In1SilFailMsk
				BitMask,
				hsw3000c01v2In1OvrFailMsk
				BitMask,
				hsw3000c01v2In1PhFailMsk
				BitMask,
				hsw3000c01v2In1PreFailMsk
				BitMask,
				hsw3000c01v2In2PhyFailMsk
				BitMask,
				hsw3000c01v2In2FmtFailMsk
				BitMask,
				hsw3000c01v2In2IncFailMsk
				BitMask,
				hsw3000c01v2In2GpiFailMsk
				BitMask,
				hsw3000c01v2In2BlkFailMsk
				BitMask,
				hsw3000c01v2In2FrzFailMsk
				BitMask,
				hsw3000c01v2In2PatFailMsk
				BitMask,
				hsw3000c01v2In2CrcFailMsk
				BitMask,
				hsw3000c01v2In2SilFailMsk
				BitMask,
				hsw3000c01v2In2OvrFailMsk
				BitMask,
				hsw3000c01v2In2PhFailMsk
				BitMask,
				hsw3000c01v2In2PreFailMsk
				BitMask,
				hsw3000c01v2RefFailMsk
				BitMask,
				hsw3000c01v2LockFailMsk
				BitMask,
				hsw3000c01v2In1AudG1p0En
				BitMask,
				hsw3000c01v2In1AudG1p1En
				BitMask,
				hsw3000c01v2In1AudG2p0En
				BitMask,
				hsw3000c01v2In1AudG2p1En
				BitMask,
				hsw3000c01v2In1AudG3p0En
				BitMask,
				hsw3000c01v2In1AudG3p1En
				BitMask,
				hsw3000c01v2In1AudG4p0En
				BitMask,
				hsw3000c01v2In1AudG4p1En
				BitMask,
				hsw3000c01v2In2AudG1p0En
				BitMask,
				hsw3000c01v2In2AudG1p1En
				BitMask,
				hsw3000c01v2In2AudG2p0En
				BitMask,
				hsw3000c01v2In2AudG2p1En
				BitMask,
				hsw3000c01v2In2AudG3p0En
				BitMask,
				hsw3000c01v2In2AudG3p1En
				BitMask,
				hsw3000c01v2In2AudG4p0En
				BitMask,
				hsw3000c01v2In2AudG4p1En
				BitMask,
				hsw3000c01v2SilenceLevel
				LevelDbfs3,
				hsw3000c01v2SilenceTime
				TimeS2,
				hsw3000c01v2OverloadLevel
				LevelDbfs4,
				hsw3000c01v2In1Fail
				BitFail,
				hsw3000c01v2In1FailTrapEnable
				AlarmEnable,
				hsw3000c01v2In2Fail
				BitFail,
				hsw3000c01v2In2FailTrapEnable
				AlarmEnable,
				hsw3000c01v2In1ExtFail
				BitFail,
				hsw3000c01v2In1ExtFailTrapEnable
				AlarmEnable,
				hsw3000c01v2In2ExtFail
				BitFail,
				hsw3000c01v2In2ExtFailTrapEnable
				AlarmEnable,
				hsw3000c01v2BlindExtFail
				BitFail,
				hsw3000c01v2BlindExtFailTrapEnable
				AlarmEnable,
				hsw3000c01v2SelOut1
				HswOutput,
				hsw3000c01v2SelOut1TrapEnable
				AlarmEnable,
				hsw3000c01v2SelOut2
				HswOutput,
				hsw3000c01v2SelOut2TrapEnable
				AlarmEnable,
				hsw3000c01v2Gpi3Stat
				BitFail,
				hsw3000c01v2Gpi3StatTrapEnable
				AlarmEnable,
				hsw3000c01v2In1PhyFail
				BitFail,
				hsw3000c01v2In1PhyFailTrapEnable
				AlarmEnable,
				hsw3000c01v2In1FmtFail
				BitFail,
				hsw3000c01v2In1FmtFailTrapEnable
				AlarmEnable,
				hsw3000c01v2In1IncFail
				BitFail,
				hsw3000c01v2In1IncFailTrapEnable
				AlarmEnable,
				hsw3000c01v2In1GpiFail
				BitFail,
				hsw3000c01v2In1GpiFailTrapEnable
				AlarmEnable,
				hsw3000c01v2In1BlkFail
				BitFail,
				hsw3000c01v2In1BlkFailTrapEnable
				AlarmEnable,
				hsw3000c01v2In1FrzFail
				BitFail,
				hsw3000c01v2In1FrzFailTrapEnable
				AlarmEnable,
				hsw3000c01v2In1PatFail
				BitFail,
				hsw3000c01v2In1PatFailTrapEnable
				AlarmEnable,
				hsw3000c01v2In1CrcFail
				BitFail,
				hsw3000c01v2In1CrcFailTrapEnable
				AlarmEnable,
				hsw3000c01v2In1SilFail
				BitFail,
				hsw3000c01v2In1SilFailTrapEnable
				AlarmEnable,
				hsw3000c01v2In1OvrFail
				BitFail,
				hsw3000c01v2In1OvrFailTrapEnable
				AlarmEnable,
				hsw3000c01v2In1PhFail
				BitFail,
				hsw3000c01v2In1PhFailTrapEnable
				AlarmEnable,
				hsw3000c01v2In1PreFail
				BitFail,
				hsw3000c01v2In1PreFailTrapEnable
				AlarmEnable,
				hsw3000c01v2In2PhyFail
				BitFail,
				hsw3000c01v2In2PhyFailTrapEnable
				AlarmEnable,
				hsw3000c01v2In2FmtFail
				BitFail,
				hsw3000c01v2In2FmtFailTrapEnable
				AlarmEnable,
				hsw3000c01v2In2IncFail
				BitFail,
				hsw3000c01v2In2IncFailTrapEnable
				AlarmEnable,
				hsw3000c01v2In2GpiFail
				BitFail,
				hsw3000c01v2In2GpiFailTrapEnable
				AlarmEnable,
				hsw3000c01v2In2BlkFail
				BitFail,
				hsw3000c01v2In2BlkFailTrapEnable
				AlarmEnable,
				hsw3000c01v2In2FrzFail
				BitFail,
				hsw3000c01v2In2FrzFailTrapEnable
				AlarmEnable,
				hsw3000c01v2In2PatFail
				BitFail,
				hsw3000c01v2In2PatFailTrapEnable
				AlarmEnable,
				hsw3000c01v2In2CrcFail
				BitFail,
				hsw3000c01v2In2CrcFailTrapEnable
				AlarmEnable,
				hsw3000c01v2In2SilFail
				BitFail,
				hsw3000c01v2In2SilFailTrapEnable
				AlarmEnable,
				hsw3000c01v2In2OvrFail
				BitFail,
				hsw3000c01v2In2OvrFailTrapEnable
				AlarmEnable,
				hsw3000c01v2In2PhFail
				BitFail,
				hsw3000c01v2In2PhFailTrapEnable
				AlarmEnable,
				hsw3000c01v2In2PreFail
				BitFail,
				hsw3000c01v2In2PreFailTrapEnable
				AlarmEnable,
				hsw3000c01v2RefFail
				BitFail,
				hsw3000c01v2RefFailTrapEnable
				AlarmEnable,
				hsw3000c01v2LockFail
				BitFail,
				hsw3000c01v2LockFailTrapEnable
				AlarmEnable,
				hsw3000c01v2BliGpiFail
				BitFail,
				hsw3000c01v2In1Format
				SdiHd3gFmt3,
				hsw3000c01v2In1FormatTrapEnable
				AlarmEnable,
				hsw3000c01v2In2Format
				SdiHd3gFmt3,
				hsw3000c01v2In2FormatTrapEnable
				AlarmEnable,
				hsw3000c01v2RefFormat
				SdiHd3gFmt3,
				hsw3000c01v2RefFormatTrapEnable
				AlarmEnable,
				hsw3000c01v2SerialNo
				SerialNo,
				hsw3000c01v2SynchroModeIn1
				Bit0Fra1Lin,
				hsw3000c01v2SynchroModeIn2
				Bit0Fra1Lin,
				hsw3000c01v2StatusMode
				StatusMode,
				hsw3000c01v2EqualPid
				UmidStatus,
				hsw3000c01v2EqualPidTrapEnable
				AlarmEnable,
				hsw3000c01v2EqualUmid
				UmidStatus,
				hsw3000c01v2EqualUmidTrapEnable
				AlarmEnable,
				hsw3000c01v2In1PidPres
				Bit0No1Yes,
				hsw3000c01v2In2PidPres
				Bit0No1Yes,
				hsw3000c01v2In1UmidPres
				Bit0No1Yes,
				hsw3000c01v2In2UmidPres
				Bit0No1Yes,
				hsw3000c01v2In1Grp1Pres
				Bit0No1Yes,
				hsw3000c01v2In1Grp1PresTrapEnable
				AlarmEnable,
				hsw3000c01v2In1Grp2Pres
				Bit0No1Yes,
				hsw3000c01v2In1Grp2PresTrapEnable
				AlarmEnable,
				hsw3000c01v2In1Grp3Pres
				Bit0No1Yes,
				hsw3000c01v2In1Grp3PresTrapEnable
				AlarmEnable,
				hsw3000c01v2In1Grp4Pres
				Bit0No1Yes,
				hsw3000c01v2In1Grp4PresTrapEnable
				AlarmEnable,
				hsw3000c01v2In1Grp1P0Err
				BitFail,
				hsw3000c01v2In1Grp1P0ErrTrapEnable
				AlarmEnable,
				hsw3000c01v2In1Grp1P1Err
				BitFail,
				hsw3000c01v2In1Grp1P1ErrTrapEnable
				AlarmEnable,
				hsw3000c01v2In1Grp2P0Err
				BitFail,
				hsw3000c01v2In1Grp2P0ErrTrapEnable
				AlarmEnable,
				hsw3000c01v2In1Grp2P1Err
				BitFail,
				hsw3000c01v2In1Grp2P1ErrTrapEnable
				AlarmEnable,
				hsw3000c01v2In1Grp3P0Err
				BitFail,
				hsw3000c01v2In1Grp3P0ErrTrapEnable
				AlarmEnable,
				hsw3000c01v2In1Grp3P1Err
				BitFail,
				hsw3000c01v2In1Grp3P1ErrTrapEnable
				AlarmEnable,
				hsw3000c01v2In1Grp4P0Err
				BitFail,
				hsw3000c01v2In1Grp4P0ErrTrapEnable
				AlarmEnable,
				hsw3000c01v2In1Grp4P1Err
				BitFail,
				hsw3000c01v2In1Grp4P1ErrTrapEnable
				AlarmEnable,
				hsw3000c01v2In2Grp1Pres
				Bit0No1Yes,
				hsw3000c01v2In2Grp1PresTrapEnable
				AlarmEnable,
				hsw3000c01v2In2Grp2Pres
				Bit0No1Yes,
				hsw3000c01v2In2Grp2PresTrapEnable
				AlarmEnable,
				hsw3000c01v2In2Grp3Pres
				Bit0No1Yes,
				hsw3000c01v2In2Grp3PresTrapEnable
				AlarmEnable,
				hsw3000c01v2In2Grp4Pres
				Bit0No1Yes,
				hsw3000c01v2In2Grp4PresTrapEnable
				AlarmEnable,
				hsw3000c01v2In2Grp1P0Err
				BitFail,
				hsw3000c01v2In2Grp1P0ErrTrapEnable
				AlarmEnable,
				hsw3000c01v2In2Grp1P1Err
				BitFail,
				hsw3000c01v2In2Grp1P1ErrTrapEnable
				AlarmEnable,
				hsw3000c01v2In2Grp2P0Err
				BitFail,
				hsw3000c01v2In2Grp2P0ErrTrapEnable
				AlarmEnable,
				hsw3000c01v2In2Grp2P1Err
				BitFail,
				hsw3000c01v2In2Grp2P1ErrTrapEnable
				AlarmEnable,
				hsw3000c01v2In2Grp3P0Err
				BitFail,
				hsw3000c01v2In2Grp3P0ErrTrapEnable
				AlarmEnable,
				hsw3000c01v2In2Grp3P1Err
				BitFail,
				hsw3000c01v2In2Grp3P1ErrTrapEnable
				AlarmEnable,
				hsw3000c01v2In2Grp4P0Err
				BitFail,
				hsw3000c01v2In2Grp4P0ErrTrapEnable
				AlarmEnable,
				hsw3000c01v2In2Grp4P1Err
				BitFail,
				hsw3000c01v2In2Grp4P1ErrTrapEnable
				AlarmEnable
			 }

		-- 1.3.6.1.4.1.10106.3.101291.1.1.1
		hsw3000c01v2Index OBJECT-TYPE
			SYNTAX ModuleIndex
			MAX-ACCESS read-only
			STATUS current
			DESCRIPTION
				"Index of HSW3000C01V2 Table"
		::= { hsw3000c01v2Entry 1 }

		-- 1.3.6.1.4.1.10106.3.101291.1.1.3
		hsw3000c01v2ActivePreset OBJECT-TYPE
			SYNTAX PresetActive
			MAX-ACCESS read-only
			STATUS current
			DESCRIPTION
				"Shows the active preset"
		::= { hsw3000c01v2Entry 3 }

		-- 1.3.6.1.4.1.10106.3.101291.1.1.5
		hsw3000c01v2LoadPreset OBJECT-TYPE
			SYNTAX PresetLoad
			MAX-ACCESS read-write
			STATUS current
			DESCRIPTION
				"Allows loading a preset"
		::= { hsw3000c01v2Entry 5 }

		-- 1.3.6.1.4.1.10106.3.101291.1.1.7
		hsw3000c01v2SavePreset OBJECT-TYPE
			SYNTAX PresetSave
			MAX-ACCESS read-write
			STATUS current
			DESCRIPTION
				"Allows saving a preset"
		::= { hsw3000c01v2Entry 7 }

		-- 1.3.6.1.4.1.10106.3.101291.1.1.9
		hsw3000c01v2StateSel OBJECT-TYPE
			SYNTAX HswState
			MAX-ACCESS read-write
			STATUS current
			DESCRIPTION
				"Shows the module's current state"
		::= { hsw3000c01v2Entry 9 }

		-- 1.3.6.1.4.1.10106.3.101291.1.1.10
		hsw3000c01v2StateSelTrapEnable OBJECT-TYPE
			SYNTAX AlarmEnable
			MAX-ACCESS read-write
			STATUS current
			DESCRIPTION
				"Shows the module's current state Trap Enable"
		::= { hsw3000c01v2Entry 10 }

		-- 1.3.6.1.4.1.10106.3.101291.1.1.11
		hsw3000c01v2SwitchMode OBJECT-TYPE
			SYNTAX HswSwMode
			MAX-ACCESS read-write
			STATUS current
			DESCRIPTION
				"Allows selecting the switching mode"
		::= { hsw3000c01v2Entry 11 }

		-- 1.3.6.1.4.1.10106.3.101291.1.1.12
		hsw3000c01v2SwitchModeTrapEnable OBJECT-TYPE
			SYNTAX AlarmEnable
			MAX-ACCESS read-write
			STATUS current
			DESCRIPTION
				"Allows selecting the switching mode Trap Enable"
		::= { hsw3000c01v2Entry 12 }

		-- 1.3.6.1.4.1.10106.3.101291.1.1.13
		hsw3000c01v2FreezeMode OBJECT-TYPE
			SYNTAX HswFreezeMode
			MAX-ACCESS read-write
			STATUS current
			DESCRIPTION
				"Allows selecting the freeze detection mode"
		::= { hsw3000c01v2Entry 13 }

		-- 1.3.6.1.4.1.10106.3.101291.1.1.15
		hsw3000c01v2BypassEnable OBJECT-TYPE
			SYNTAX Bit0Dis1Ena
			MAX-ACCESS read-write
			STATUS current
			DESCRIPTION
				"Allows activating the rear board bypass"
		::= { hsw3000c01v2Entry 15 }

		-- 1.3.6.1.4.1.10106.3.101291.1.1.16
		hsw3000c01v2BypassEnableTrapEnable OBJECT-TYPE
			SYNTAX AlarmEnable
			MAX-ACCESS read-write
			STATUS current
			DESCRIPTION
				"Allows activating the rear board bypass Trap Enable"
		::= { hsw3000c01v2Entry 16 }

		-- 1.3.6.1.4.1.10106.3.101291.1.1.17
		hsw3000c01v2InpFailMode OBJECT-TYPE
			SYNTAX Bit0No1Yes
			MAX-ACCESS read-write
			STATUS current
			DESCRIPTION
				"Selects if the output is muted when the selected input fails"
		::= { hsw3000c01v2Entry 17 }

		-- 1.3.6.1.4.1.10106.3.101291.1.1.19
		hsw3000c01v2OperatingMode OBJECT-TYPE
			SYNTAX HswOperMode
			MAX-ACCESS read-write
			STATUS current
			DESCRIPTION
				"Allows selecting the operating mode"
		::= { hsw3000c01v2Entry 19 }

		-- 1.3.6.1.4.1.10106.3.101291.1.1.20
		hsw3000c01v2OperatingModeTrapEnable OBJECT-TYPE
			SYNTAX AlarmEnable
			MAX-ACCESS read-write
			STATUS current
			DESCRIPTION
				"Allows selecting the operating mode Trap Enable"
		::= { hsw3000c01v2Entry 20 }

		-- 1.3.6.1.4.1.10106.3.101291.1.1.21
		hsw3000c01v2StateAMap OBJECT-TYPE
			SYNTAX HswMapState
			MAX-ACCESS read-write
			STATUS current
			DESCRIPTION
				"Allow selecting the input to output mapping when state A is selected"
		::= { hsw3000c01v2Entry 21 }

		-- 1.3.6.1.4.1.10106.3.101291.1.1.23
		hsw3000c01v2StateBMap OBJECT-TYPE
			SYNTAX HswMapState
			MAX-ACCESS read-write
			STATUS current
			DESCRIPTION
				"Allow selecting the input to output mapping when state B is selected"
		::= { hsw3000c01v2Entry 23 }

		-- 1.3.6.1.4.1.10106.3.101291.1.1.25
		hsw3000c01v2StateAGpo OBJECT-TYPE
			SYNTAX HswGpoState
			MAX-ACCESS read-write
			STATUS current
			DESCRIPTION
				"Allow selecting the GPO configuration when state A is selected"
		::= { hsw3000c01v2Entry 25 }

		-- 1.3.6.1.4.1.10106.3.101291.1.1.27
		hsw3000c01v2StateBGpo OBJECT-TYPE
			SYNTAX HswGpoState
			MAX-ACCESS read-write
			STATUS current
			DESCRIPTION
				"Allow selecting the GPO configuration when state B is selected"
		::= { hsw3000c01v2Entry 27 }

		-- 1.3.6.1.4.1.10106.3.101291.1.1.29
		hsw3000c01v2AnaRefFmt OBJECT-TYPE
			SYNTAX SdiHd3gFmt5
			MAX-ACCESS read-write
			STATUS current
			DESCRIPTION
				"Analog reference input format"
		::= { hsw3000c01v2Entry 29 }

		-- 1.3.6.1.4.1.10106.3.101291.1.1.31
		hsw3000c01v2In1StChange OBJECT-TYPE
			SYNTAX Bit0No1Yes
			MAX-ACCESS read-write
			STATUS current
			DESCRIPTION
				"Signals a change in fail status"
		::= { hsw3000c01v2Entry 31 }

		-- 1.3.6.1.4.1.10106.3.101291.1.1.33
		hsw3000c01v2In2StChange OBJECT-TYPE
			SYNTAX Bit0No1Yes
			MAX-ACCESS read-write
			STATUS current
			DESCRIPTION
				"Signals a change in fail status"
		::= { hsw3000c01v2Entry 33 }

		-- 1.3.6.1.4.1.10106.3.101291.1.1.35
		hsw3000c01v2Gpi1StChange OBJECT-TYPE
			SYNTAX Bit0No1Yes
			MAX-ACCESS read-write
			STATUS current
			DESCRIPTION
				"Signals a change in GPI fail status"
		::= { hsw3000c01v2Entry 35 }

		-- 1.3.6.1.4.1.10106.3.101291.1.1.37
		hsw3000c01v2Gpi2StChange OBJECT-TYPE
			SYNTAX Bit0No1Yes
			MAX-ACCESS read-write
			STATUS current
			DESCRIPTION
				"Signals a change in GPI fail status"
		::= { hsw3000c01v2Entry 37 }

		-- 1.3.6.1.4.1.10106.3.101291.1.1.39
		hsw3000c01v2Gpi3StChange OBJECT-TYPE
			SYNTAX Bit0No1Yes
			MAX-ACCESS read-write
			STATUS current
			DESCRIPTION
				"Signals a change in GPI fail status (GPI2B)"
		::= { hsw3000c01v2Entry 39 }

		-- 1.3.6.1.4.1.10106.3.101291.1.1.41
		hsw3000c01v2InputChange OBJECT-TYPE
			SYNTAX Bit0No1Yes
			MAX-ACCESS read-write
			STATUS current
			DESCRIPTION
				"Signals a change in selected input"
		::= { hsw3000c01v2Entry 41 }

		-- 1.3.6.1.4.1.10106.3.101291.1.1.43
		hsw3000c01v2VDelay OBJECT-TYPE
			SYNTAX DelayLines2
			MAX-ACCESS read-write
			STATUS current
			DESCRIPTION
				"Allows adjusting the video vertical delay"
		::= { hsw3000c01v2Entry 43 }

		-- 1.3.6.1.4.1.10106.3.101291.1.1.45
		hsw3000c01v2HDelay OBJECT-TYPE
			SYNTAX DelayPixel5
			MAX-ACCESS read-write
			STATUS current
			DESCRIPTION
				"Allows adjusting the video horizontal delay"
		::= { hsw3000c01v2Entry 45 }

		-- 1.3.6.1.4.1.10106.3.101291.1.1.47
		hsw3000c01v2Holdoff OBJECT-TYPE
			SYNTAX TimeS2
			MAX-ACCESS read-write
			STATUS current
			DESCRIPTION
				"Elapsed time after a switch event before a new switch occurs"
		::= { hsw3000c01v2Entry 47 }

		-- 1.3.6.1.4.1.10106.3.101291.1.1.49
		hsw3000c01v2PhyFailTim OBJECT-TYPE
			SYNTAX HswTiming
			MAX-ACCESS read-write
			STATUS current
			DESCRIPTION
				"Allows selecting the desired timing for the physical fail"
		::= { hsw3000c01v2Entry 49 }

		-- 1.3.6.1.4.1.10106.3.101291.1.1.51
		hsw3000c01v2FmtFailTim OBJECT-TYPE
			SYNTAX HswTiming
			MAX-ACCESS read-write
			STATUS current
			DESCRIPTION
				"Allows selecting the desired timing for the format fail"
		::= { hsw3000c01v2Entry 51 }

		-- 1.3.6.1.4.1.10106.3.101291.1.1.53
		hsw3000c01v2IncFailTim OBJECT-TYPE
			SYNTAX HswTiming
			MAX-ACCESS read-write
			STATUS current
			DESCRIPTION
				"Allows selecting the desired timing for the incompatible format fail"
		::= { hsw3000c01v2Entry 53 }

		-- 1.3.6.1.4.1.10106.3.101291.1.1.55
		hsw3000c01v2GpiFailTim OBJECT-TYPE
			SYNTAX HswTiming
			MAX-ACCESS read-write
			STATUS current
			DESCRIPTION
				"Allows selecting the desired timing for the GPI fail"
		::= { hsw3000c01v2Entry 55 }

		-- 1.3.6.1.4.1.10106.3.101291.1.1.57
		hsw3000c01v2BlkFailTim OBJECT-TYPE
			SYNTAX HswTiming
			MAX-ACCESS read-write
			STATUS current
			DESCRIPTION
				"Allows selecting the desired timing for the black fail"
		::= { hsw3000c01v2Entry 57 }

		-- 1.3.6.1.4.1.10106.3.101291.1.1.59
		hsw3000c01v2FrzFailTim OBJECT-TYPE
			SYNTAX HswTiming
			MAX-ACCESS read-write
			STATUS current
			DESCRIPTION
				"Allows selecting the desired timing for the freeze fail"
		::= { hsw3000c01v2Entry 59 }

		-- 1.3.6.1.4.1.10106.3.101291.1.1.61
		hsw3000c01v2PatFailTim OBJECT-TYPE
			SYNTAX HswTiming
			MAX-ACCESS read-write
			STATUS current
			DESCRIPTION
				"Allows selecting the desired timing for the pattern fail"
		::= { hsw3000c01v2Entry 61 }

		-- 1.3.6.1.4.1.10106.3.101291.1.1.63
		hsw3000c01v2CrcFailTim OBJECT-TYPE
			SYNTAX HswTiming
			MAX-ACCESS read-write
			STATUS current
			DESCRIPTION
				"Allows selecting the desired timing for the EDH/CRC"
		::= { hsw3000c01v2Entry 63 }

		-- 1.3.6.1.4.1.10106.3.101291.1.1.65
		hsw3000c01v2SilFailTim OBJECT-TYPE
			SYNTAX HswTiming
			MAX-ACCESS read-write
			STATUS current
			DESCRIPTION
				"Allows selecting the desired timing for the audio silence fail"
		::= { hsw3000c01v2Entry 65 }

		-- 1.3.6.1.4.1.10106.3.101291.1.1.67
		hsw3000c01v2OvrFailTim OBJECT-TYPE
			SYNTAX HswTiming
			MAX-ACCESS read-write
			STATUS current
			DESCRIPTION
				"Allows selecting the desired timing for the audio overload fail"
		::= { hsw3000c01v2Entry 67 }

		-- 1.3.6.1.4.1.10106.3.101291.1.1.69
		hsw3000c01v2PhFailTim OBJECT-TYPE
			SYNTAX HswTiming
			MAX-ACCESS read-write
			STATUS current
			DESCRIPTION
				"Allows selecting the desired timing for the audio phase fail"
		::= { hsw3000c01v2Entry 69 }

		-- 1.3.6.1.4.1.10106.3.101291.1.1.71
		hsw3000c01v2PresFailTim OBJECT-TYPE
			SYNTAX HswTiming
			MAX-ACCESS read-write
			STATUS current
			DESCRIPTION
				"Allows selecting the desired timing for the audio presence fail"
		::= { hsw3000c01v2Entry 71 }

		-- 1.3.6.1.4.1.10106.3.101291.1.1.73
		hsw3000c01v2ActPer1 OBJECT-TYPE
			SYNTAX TimeS2
			MAX-ACCESS read-write
			STATUS current
			DESCRIPTION
				"Activation time used in timing 1"
		::= { hsw3000c01v2Entry 73 }

		-- 1.3.6.1.4.1.10106.3.101291.1.1.75
		hsw3000c01v2DeactPer1 OBJECT-TYPE
			SYNTAX TimeS2
			MAX-ACCESS read-write
			STATUS current
			DESCRIPTION
				"Deactivation time used in timing 1"
		::= { hsw3000c01v2Entry 75 }

		-- 1.3.6.1.4.1.10106.3.101291.1.1.77
		hsw3000c01v2ActPer2 OBJECT-TYPE
			SYNTAX TimeS2
			MAX-ACCESS read-write
			STATUS current
			DESCRIPTION
				"Activation time used in timing 2"
		::= { hsw3000c01v2Entry 77 }

		-- 1.3.6.1.4.1.10106.3.101291.1.1.79
		hsw3000c01v2DeactPer2 OBJECT-TYPE
			SYNTAX TimeS2
			MAX-ACCESS read-write
			STATUS current
			DESCRIPTION
				"Deactivation time used in timing 2"
		::= { hsw3000c01v2Entry 79 }

		-- 1.3.6.1.4.1.10106.3.101291.1.1.81
		hsw3000c01v2CrcThreshold OBJECT-TYPE
			SYNTAX Rate2
			MAX-ACCESS read-write
			STATUS current
			DESCRIPTION
				"Allows adjusting the threshold that activates the EDH/CRC fail"
		::= { hsw3000c01v2Entry 81 }

		-- 1.3.6.1.4.1.10106.3.101291.1.1.83
		hsw3000c01v2BlackThreshold OBJECT-TYPE
			SYNTAX BlackThreshold
			MAX-ACCESS read-write
			STATUS current
			DESCRIPTION
				"Allows adjusting the threshold thas activates the black fail"
		::= { hsw3000c01v2Entry 83 }

		-- 1.3.6.1.4.1.10106.3.101291.1.1.85
		hsw3000c01v2VertFrozenWin OBJECT-TYPE
			SYNTAX Rate1
			MAX-ACCESS read-write
			STATUS current
			DESCRIPTION
				"Allows adjusting the vertical size of the window used in the freeze detector"
		::= { hsw3000c01v2Entry 85 }

		-- 1.3.6.1.4.1.10106.3.101291.1.1.87
		hsw3000c01v2HtalFrozenWin OBJECT-TYPE
			SYNTAX Rate1
			MAX-ACCESS read-write
			STATUS current
			DESCRIPTION
				"Allows adjusting the horizontal size of the window used in the freeze detector"
		::= { hsw3000c01v2Entry 87 }

		-- 1.3.6.1.4.1.10106.3.101291.1.1.89
		hsw3000c01v2In1PhyFailMsk OBJECT-TYPE
			SYNTAX BitMask
			MAX-ACCESS read-write
			STATUS current
			DESCRIPTION
				"Allows masking the signal absence fail"
		::= { hsw3000c01v2Entry 89 }

		-- 1.3.6.1.4.1.10106.3.101291.1.1.91
		hsw3000c01v2In1FmtFailMsk OBJECT-TYPE
			SYNTAX BitMask
			MAX-ACCESS read-write
			STATUS current
			DESCRIPTION
				"Allows masking the format fail"
		::= { hsw3000c01v2Entry 91 }

		-- 1.3.6.1.4.1.10106.3.101291.1.1.93
		hsw3000c01v2In1IncFailMsk OBJECT-TYPE
			SYNTAX BitMask
			MAX-ACCESS read-write
			STATUS current
			DESCRIPTION
				"Allows masking the incompatible format fail"
		::= { hsw3000c01v2Entry 93 }

		-- 1.3.6.1.4.1.10106.3.101291.1.1.95
		hsw3000c01v2In1GpiFailMsk OBJECT-TYPE
			SYNTAX BitMask
			MAX-ACCESS read-write
			STATUS current
			DESCRIPTION
				"Allows masking the GPI fail"
		::= { hsw3000c01v2Entry 95 }

		-- 1.3.6.1.4.1.10106.3.101291.1.1.97
		hsw3000c01v2In1BlkFailMsk OBJECT-TYPE
			SYNTAX BitMask
			MAX-ACCESS read-write
			STATUS current
			DESCRIPTION
				"Allows masking the black signal fail"
		::= { hsw3000c01v2Entry 97 }

		-- 1.3.6.1.4.1.10106.3.101291.1.1.99
		hsw3000c01v2In1FrzFailMsk OBJECT-TYPE
			SYNTAX BitMask
			MAX-ACCESS read-write
			STATUS current
			DESCRIPTION
				"Allows masking the freeze signal fail"
		::= { hsw3000c01v2Entry 99 }

		-- 1.3.6.1.4.1.10106.3.101291.1.1.101
		hsw3000c01v2In1PatFailMsk OBJECT-TYPE
			SYNTAX BitMask
			MAX-ACCESS read-write
			STATUS current
			DESCRIPTION
				"Allows masking the video pattern fail"
		::= { hsw3000c01v2Entry 101 }

		-- 1.3.6.1.4.1.10106.3.101291.1.1.103
		hsw3000c01v2In1CrcFailMsk OBJECT-TYPE
			SYNTAX BitMask
			MAX-ACCESS read-write
			STATUS current
			DESCRIPTION
				"Allows masking the EDH/CRC"
		::= { hsw3000c01v2Entry 103 }

		-- 1.3.6.1.4.1.10106.3.101291.1.1.105
		hsw3000c01v2In1SilFailMsk OBJECT-TYPE
			SYNTAX BitMask
			MAX-ACCESS read-write
			STATUS current
			DESCRIPTION
				"Allows masking the audio silence fail"
		::= { hsw3000c01v2Entry 105 }

		-- 1.3.6.1.4.1.10106.3.101291.1.1.107
		hsw3000c01v2In1OvrFailMsk OBJECT-TYPE
			SYNTAX BitMask
			MAX-ACCESS read-write
			STATUS current
			DESCRIPTION
				"Allows masking the audio overload fail"
		::= { hsw3000c01v2Entry 107 }

		-- 1.3.6.1.4.1.10106.3.101291.1.1.109
		hsw3000c01v2In1PhFailMsk OBJECT-TYPE
			SYNTAX BitMask
			MAX-ACCESS read-write
			STATUS current
			DESCRIPTION
				"Allows masking the audio phase fail"
		::= { hsw3000c01v2Entry 109 }

		-- 1.3.6.1.4.1.10106.3.101291.1.1.111
		hsw3000c01v2In1PreFailMsk OBJECT-TYPE
			SYNTAX BitMask
			MAX-ACCESS read-write
			STATUS current
			DESCRIPTION
				"Allows masking the audio presence fail"
		::= { hsw3000c01v2Entry 111 }

		-- 1.3.6.1.4.1.10106.3.101291.1.1.113
		hsw3000c01v2In2PhyFailMsk OBJECT-TYPE
			SYNTAX BitMask
			MAX-ACCESS read-write
			STATUS current
			DESCRIPTION
				"Allows masking the signal absence fail"
		::= { hsw3000c01v2Entry 113 }

		-- 1.3.6.1.4.1.10106.3.101291.1.1.115
		hsw3000c01v2In2FmtFailMsk OBJECT-TYPE
			SYNTAX BitMask
			MAX-ACCESS read-write
			STATUS current
			DESCRIPTION
				"Allows masking the format fail"
		::= { hsw3000c01v2Entry 115 }

		-- 1.3.6.1.4.1.10106.3.101291.1.1.117
		hsw3000c01v2In2IncFailMsk OBJECT-TYPE
			SYNTAX BitMask
			MAX-ACCESS read-write
			STATUS current
			DESCRIPTION
				"Allows masking the incompatible format fail"
		::= { hsw3000c01v2Entry 117 }

		-- 1.3.6.1.4.1.10106.3.101291.1.1.119
		hsw3000c01v2In2GpiFailMsk OBJECT-TYPE
			SYNTAX BitMask
			MAX-ACCESS read-write
			STATUS current
			DESCRIPTION
				"Allows masking the GPI fail"
		::= { hsw3000c01v2Entry 119 }

		-- 1.3.6.1.4.1.10106.3.101291.1.1.121
		hsw3000c01v2In2BlkFailMsk OBJECT-TYPE
			SYNTAX BitMask
			MAX-ACCESS read-write
			STATUS current
			DESCRIPTION
				"Allows masking the black signal fail"
		::= { hsw3000c01v2Entry 121 }

		-- 1.3.6.1.4.1.10106.3.101291.1.1.123
		hsw3000c01v2In2FrzFailMsk OBJECT-TYPE
			SYNTAX BitMask
			MAX-ACCESS read-write
			STATUS current
			DESCRIPTION
				"Allows masking the freeze signal fail"
		::= { hsw3000c01v2Entry 123 }

		-- 1.3.6.1.4.1.10106.3.101291.1.1.125
		hsw3000c01v2In2PatFailMsk OBJECT-TYPE
			SYNTAX BitMask
			MAX-ACCESS read-write
			STATUS current
			DESCRIPTION
				"Allows masking the video pattern fail"
		::= { hsw3000c01v2Entry 125 }

		-- 1.3.6.1.4.1.10106.3.101291.1.1.127
		hsw3000c01v2In2CrcFailMsk OBJECT-TYPE
			SYNTAX BitMask
			MAX-ACCESS read-write
			STATUS current
			DESCRIPTION
				"Allows masking the EDH/CRC"
		::= { hsw3000c01v2Entry 127 }

		-- 1.3.6.1.4.1.10106.3.101291.1.1.129
		hsw3000c01v2In2SilFailMsk OBJECT-TYPE
			SYNTAX BitMask
			MAX-ACCESS read-write
			STATUS current
			DESCRIPTION
				"Allows masking the audio silence fail"
		::= { hsw3000c01v2Entry 129 }

		-- 1.3.6.1.4.1.10106.3.101291.1.1.131
		hsw3000c01v2In2OvrFailMsk OBJECT-TYPE
			SYNTAX BitMask
			MAX-ACCESS read-write
			STATUS current
			DESCRIPTION
				"Allows masking the audio overload fail"
		::= { hsw3000c01v2Entry 131 }

		-- 1.3.6.1.4.1.10106.3.101291.1.1.133
		hsw3000c01v2In2PhFailMsk OBJECT-TYPE
			SYNTAX BitMask
			MAX-ACCESS read-write
			STATUS current
			DESCRIPTION
				"Allows masking the audio phase fail"
		::= { hsw3000c01v2Entry 133 }

		-- 1.3.6.1.4.1.10106.3.101291.1.1.135
		hsw3000c01v2In2PreFailMsk OBJECT-TYPE
			SYNTAX BitMask
			MAX-ACCESS read-write
			STATUS current
			DESCRIPTION
				"Allows masking the audio presence fail"
		::= { hsw3000c01v2Entry 135 }

		-- 1.3.6.1.4.1.10106.3.101291.1.1.137
		hsw3000c01v2RefFailMsk OBJECT-TYPE
			SYNTAX BitMask
			MAX-ACCESS read-write
			STATUS current
			DESCRIPTION
				"Allows masking the reference absence fail"
		::= { hsw3000c01v2Entry 137 }

		-- 1.3.6.1.4.1.10106.3.101291.1.1.139
		hsw3000c01v2LockFailMsk OBJECT-TYPE
			SYNTAX BitMask
			MAX-ACCESS read-write
			STATUS current
			DESCRIPTION
				"Allows masking the reference unlock fail"
		::= { hsw3000c01v2Entry 139 }

		-- 1.3.6.1.4.1.10106.3.101291.1.1.141
		hsw3000c01v2In1AudG1p0En OBJECT-TYPE
			SYNTAX BitMask
			MAX-ACCESS read-write
			STATUS current
			DESCRIPTION
				"Allows masking the audio in group 1 pair 0"
		::= { hsw3000c01v2Entry 141 }

		-- 1.3.6.1.4.1.10106.3.101291.1.1.143
		hsw3000c01v2In1AudG1p1En OBJECT-TYPE
			SYNTAX BitMask
			MAX-ACCESS read-write
			STATUS current
			DESCRIPTION
				"Allows masking the audio in group 1 pair 1"
		::= { hsw3000c01v2Entry 143 }

		-- 1.3.6.1.4.1.10106.3.101291.1.1.145
		hsw3000c01v2In1AudG2p0En OBJECT-TYPE
			SYNTAX BitMask
			MAX-ACCESS read-write
			STATUS current
			DESCRIPTION
				"Allows masking the audio in group 2 pair 0"
		::= { hsw3000c01v2Entry 145 }

		-- 1.3.6.1.4.1.10106.3.101291.1.1.147
		hsw3000c01v2In1AudG2p1En OBJECT-TYPE
			SYNTAX BitMask
			MAX-ACCESS read-write
			STATUS current
			DESCRIPTION
				"Allows masking the audio in group 2 pair 1"
		::= { hsw3000c01v2Entry 147 }

		-- 1.3.6.1.4.1.10106.3.101291.1.1.149
		hsw3000c01v2In1AudG3p0En OBJECT-TYPE
			SYNTAX BitMask
			MAX-ACCESS read-write
			STATUS current
			DESCRIPTION
				"Allows masking the audio in group 3 pair 0"
		::= { hsw3000c01v2Entry 149 }

		-- 1.3.6.1.4.1.10106.3.101291.1.1.151
		hsw3000c01v2In1AudG3p1En OBJECT-TYPE
			SYNTAX BitMask
			MAX-ACCESS read-write
			STATUS current
			DESCRIPTION
				"Allows masking the audio in group 3 pair 1"
		::= { hsw3000c01v2Entry 151 }

		-- 1.3.6.1.4.1.10106.3.101291.1.1.153
		hsw3000c01v2In1AudG4p0En OBJECT-TYPE
			SYNTAX BitMask
			MAX-ACCESS read-write
			STATUS current
			DESCRIPTION
				"Allows masking the audio in group 4 pair 0"
		::= { hsw3000c01v2Entry 153 }

		-- 1.3.6.1.4.1.10106.3.101291.1.1.155
		hsw3000c01v2In1AudG4p1En OBJECT-TYPE
			SYNTAX BitMask
			MAX-ACCESS read-write
			STATUS current
			DESCRIPTION
				"Allows masking the audio in group 4 pair 1"
		::= { hsw3000c01v2Entry 155 }

		-- 1.3.6.1.4.1.10106.3.101291.1.1.157
		hsw3000c01v2In2AudG1p0En OBJECT-TYPE
			SYNTAX BitMask
			MAX-ACCESS read-write
			STATUS current
			DESCRIPTION
				"Allows masking the audio in group 1 pair 0"
		::= { hsw3000c01v2Entry 157 }

		-- 1.3.6.1.4.1.10106.3.101291.1.1.159
		hsw3000c01v2In2AudG1p1En OBJECT-TYPE
			SYNTAX BitMask
			MAX-ACCESS read-write
			STATUS current
			DESCRIPTION
				"Allows masking the audio in group 1 pair 1"
		::= { hsw3000c01v2Entry 159 }

		-- 1.3.6.1.4.1.10106.3.101291.1.1.161
		hsw3000c01v2In2AudG2p0En OBJECT-TYPE
			SYNTAX BitMask
			MAX-ACCESS read-write
			STATUS current
			DESCRIPTION
				"Allows masking the audio in group 2 pair 0"
		::= { hsw3000c01v2Entry 161 }

		-- 1.3.6.1.4.1.10106.3.101291.1.1.163
		hsw3000c01v2In2AudG2p1En OBJECT-TYPE
			SYNTAX BitMask
			MAX-ACCESS read-write
			STATUS current
			DESCRIPTION
				"Allows masking the audio in group 2 pair 1"
		::= { hsw3000c01v2Entry 163 }

		-- 1.3.6.1.4.1.10106.3.101291.1.1.165
		hsw3000c01v2In2AudG3p0En OBJECT-TYPE
			SYNTAX BitMask
			MAX-ACCESS read-write
			STATUS current
			DESCRIPTION
				"Allows masking the audio in group 3 pair 0"
		::= { hsw3000c01v2Entry 165 }

		-- 1.3.6.1.4.1.10106.3.101291.1.1.167
		hsw3000c01v2In2AudG3p1En OBJECT-TYPE
			SYNTAX BitMask
			MAX-ACCESS read-write
			STATUS current
			DESCRIPTION
				"Allows masking the audio in group 3 pair 1"
		::= { hsw3000c01v2Entry 167 }

		-- 1.3.6.1.4.1.10106.3.101291.1.1.169
		hsw3000c01v2In2AudG4p0En OBJECT-TYPE
			SYNTAX BitMask
			MAX-ACCESS read-write
			STATUS current
			DESCRIPTION
				"Allows masking the audio in group 4 pair 0"
		::= { hsw3000c01v2Entry 169 }

		-- 1.3.6.1.4.1.10106.3.101291.1.1.171
		hsw3000c01v2In2AudG4p1En OBJECT-TYPE
			SYNTAX BitMask
			MAX-ACCESS read-write
			STATUS current
			DESCRIPTION
				"Allows masking the audio in group 4 pair 1"
		::= { hsw3000c01v2Entry 171 }

		-- 1.3.6.1.4.1.10106.3.101291.1.1.173
		hsw3000c01v2SilenceLevel OBJECT-TYPE
			SYNTAX LevelDbfs3
			MAX-ACCESS read-write
			STATUS current
			DESCRIPTION
				"Allows adjusting the threshold level for the silence detector"
		::= { hsw3000c01v2Entry 173 }

		-- 1.3.6.1.4.1.10106.3.101291.1.1.175
		hsw3000c01v2SilenceTime OBJECT-TYPE
			SYNTAX TimeS2
			MAX-ACCESS read-write
			STATUS current
			DESCRIPTION
				"Allows adjusting the time for the silence detector"
		::= { hsw3000c01v2Entry 175 }

		-- 1.3.6.1.4.1.10106.3.101291.1.1.177
		hsw3000c01v2OverloadLevel OBJECT-TYPE
			SYNTAX LevelDbfs4
			MAX-ACCESS read-write
			STATUS current
			DESCRIPTION
				"Allows adjusting the threshold level for the overload detector"
		::= { hsw3000c01v2Entry 177 }

		-- 1.3.6.1.4.1.10106.3.101291.1.1.179
		hsw3000c01v2In1Fail OBJECT-TYPE
			SYNTAX BitFail
			MAX-ACCESS read-only
			STATUS current
			DESCRIPTION
				"Input 1 fail"
		::= { hsw3000c01v2Entry 179 }

		-- 1.3.6.1.4.1.10106.3.101291.1.1.180
		hsw3000c01v2In1FailTrapEnable OBJECT-TYPE
			SYNTAX AlarmEnable
			MAX-ACCESS read-write
			STATUS current
			DESCRIPTION
				"Input 1 fail Trap Enable"
		::= { hsw3000c01v2Entry 180 }

		-- 1.3.6.1.4.1.10106.3.101291.1.1.181
		hsw3000c01v2In2Fail OBJECT-TYPE
			SYNTAX BitFail
			MAX-ACCESS read-only
			STATUS current
			DESCRIPTION
				"Input 2 fail"
		::= { hsw3000c01v2Entry 181 }

		-- 1.3.6.1.4.1.10106.3.101291.1.1.182
		hsw3000c01v2In2FailTrapEnable OBJECT-TYPE
			SYNTAX AlarmEnable
			MAX-ACCESS read-write
			STATUS current
			DESCRIPTION
				"Input 2 fail Trap Enable"
		::= { hsw3000c01v2Entry 182 }

		-- 1.3.6.1.4.1.10106.3.101291.1.1.183
		hsw3000c01v2In1ExtFail OBJECT-TYPE
			SYNTAX BitFail
			MAX-ACCESS read-only
			STATUS current
			DESCRIPTION
				"Input 1 GPI fail (GPI1A)"
		::= { hsw3000c01v2Entry 183 }

		-- 1.3.6.1.4.1.10106.3.101291.1.1.184
		hsw3000c01v2In1ExtFailTrapEnable OBJECT-TYPE
			SYNTAX AlarmEnable
			MAX-ACCESS read-write
			STATUS current
			DESCRIPTION
				"Input 1 GPI fail (GPI1A) Trap Enable"
		::= { hsw3000c01v2Entry 184 }

		-- 1.3.6.1.4.1.10106.3.101291.1.1.185
		hsw3000c01v2In2ExtFail OBJECT-TYPE
			SYNTAX BitFail
			MAX-ACCESS read-only
			STATUS current
			DESCRIPTION
				"Input 2 GPI fail (GPI2A)"
		::= { hsw3000c01v2Entry 185 }

		-- 1.3.6.1.4.1.10106.3.101291.1.1.186
		hsw3000c01v2In2ExtFailTrapEnable OBJECT-TYPE
			SYNTAX AlarmEnable
			MAX-ACCESS read-write
			STATUS current
			DESCRIPTION
				"Input 2 GPI fail (GPI2A) Trap Enable"
		::= { hsw3000c01v2Entry 186 }

		-- 1.3.6.1.4.1.10106.3.101291.1.1.187
		hsw3000c01v2BlindExtFail OBJECT-TYPE
			SYNTAX BitFail
			MAX-ACCESS read-only
			STATUS current
			DESCRIPTION
				"Blind halfauto control GPI fail (GPI2B)"
		::= { hsw3000c01v2Entry 187 }

		-- 1.3.6.1.4.1.10106.3.101291.1.1.188
		hsw3000c01v2BlindExtFailTrapEnable OBJECT-TYPE
			SYNTAX AlarmEnable
			MAX-ACCESS read-write
			STATUS current
			DESCRIPTION
				"Blind halfauto control GPI fail (GPI2B) Trap Enable"
		::= { hsw3000c01v2Entry 188 }

		-- 1.3.6.1.4.1.10106.3.101291.1.1.189
		hsw3000c01v2SelOut1 OBJECT-TYPE
			SYNTAX HswOutput
			MAX-ACCESS read-only
			STATUS current
			DESCRIPTION
				"Output 1"
		::= { hsw3000c01v2Entry 189 }

		-- 1.3.6.1.4.1.10106.3.101291.1.1.190
		hsw3000c01v2SelOut1TrapEnable OBJECT-TYPE
			SYNTAX AlarmEnable
			MAX-ACCESS read-write
			STATUS current
			DESCRIPTION
				"Output 1 Trap Enable"
		::= { hsw3000c01v2Entry 190 }

		-- 1.3.6.1.4.1.10106.3.101291.1.1.191
		hsw3000c01v2SelOut2 OBJECT-TYPE
			SYNTAX HswOutput
			MAX-ACCESS read-only
			STATUS current
			DESCRIPTION
				"Output 2"
		::= { hsw3000c01v2Entry 191 }

		-- 1.3.6.1.4.1.10106.3.101291.1.1.192
		hsw3000c01v2SelOut2TrapEnable OBJECT-TYPE
			SYNTAX AlarmEnable
			MAX-ACCESS read-write
			STATUS current
			DESCRIPTION
				"Output 2 Trap Enable"
		::= { hsw3000c01v2Entry 192 }

		-- 1.3.6.1.4.1.10106.3.101291.1.1.193
		hsw3000c01v2Gpi3Stat OBJECT-TYPE
			SYNTAX BitFail
			MAX-ACCESS read-only
			STATUS current
			DESCRIPTION
				"GPI1B status (used in remote control)"
		::= { hsw3000c01v2Entry 193 }

		-- 1.3.6.1.4.1.10106.3.101291.1.1.194
		hsw3000c01v2Gpi3StatTrapEnable OBJECT-TYPE
			SYNTAX AlarmEnable
			MAX-ACCESS read-write
			STATUS current
			DESCRIPTION
				"GPI1B status (used in remote control) Trap Enable"
		::= { hsw3000c01v2Entry 194 }

		-- 1.3.6.1.4.1.10106.3.101291.1.1.195
		hsw3000c01v2In1PhyFail OBJECT-TYPE
			SYNTAX BitFail
			MAX-ACCESS read-only
			STATUS current
			DESCRIPTION
				"Absence fail"
		::= { hsw3000c01v2Entry 195 }

		-- 1.3.6.1.4.1.10106.3.101291.1.1.196
		hsw3000c01v2In1PhyFailTrapEnable OBJECT-TYPE
			SYNTAX AlarmEnable
			MAX-ACCESS read-write
			STATUS current
			DESCRIPTION
				"Absence fail Trap Enable"
		::= { hsw3000c01v2Entry 196 }

		-- 1.3.6.1.4.1.10106.3.101291.1.1.197
		hsw3000c01v2In1FmtFail OBJECT-TYPE
			SYNTAX BitFail
			MAX-ACCESS read-only
			STATUS current
			DESCRIPTION
				"Format fail"
		::= { hsw3000c01v2Entry 197 }

		-- 1.3.6.1.4.1.10106.3.101291.1.1.198
		hsw3000c01v2In1FmtFailTrapEnable OBJECT-TYPE
			SYNTAX AlarmEnable
			MAX-ACCESS read-write
			STATUS current
			DESCRIPTION
				"Format fail Trap Enable"
		::= { hsw3000c01v2Entry 198 }

		-- 1.3.6.1.4.1.10106.3.101291.1.1.199
		hsw3000c01v2In1IncFail OBJECT-TYPE
			SYNTAX BitFail
			MAX-ACCESS read-only
			STATUS current
			DESCRIPTION
				"Incompatible format fail"
		::= { hsw3000c01v2Entry 199 }

		-- 1.3.6.1.4.1.10106.3.101291.1.1.200
		hsw3000c01v2In1IncFailTrapEnable OBJECT-TYPE
			SYNTAX AlarmEnable
			MAX-ACCESS read-write
			STATUS current
			DESCRIPTION
				"Incompatible format fail Trap Enable"
		::= { hsw3000c01v2Entry 200 }

		-- 1.3.6.1.4.1.10106.3.101291.1.1.201
		hsw3000c01v2In1GpiFail OBJECT-TYPE
			SYNTAX BitFail
			MAX-ACCESS read-only
			STATUS current
			DESCRIPTION
				"External GPI fail"
		::= { hsw3000c01v2Entry 201 }

		-- 1.3.6.1.4.1.10106.3.101291.1.1.202
		hsw3000c01v2In1GpiFailTrapEnable OBJECT-TYPE
			SYNTAX AlarmEnable
			MAX-ACCESS read-write
			STATUS current
			DESCRIPTION
				"External GPI fail Trap Enable"
		::= { hsw3000c01v2Entry 202 }

		-- 1.3.6.1.4.1.10106.3.101291.1.1.203
		hsw3000c01v2In1BlkFail OBJECT-TYPE
			SYNTAX BitFail
			MAX-ACCESS read-only
			STATUS current
			DESCRIPTION
				"Black signal fail"
		::= { hsw3000c01v2Entry 203 }

		-- 1.3.6.1.4.1.10106.3.101291.1.1.204
		hsw3000c01v2In1BlkFailTrapEnable OBJECT-TYPE
			SYNTAX AlarmEnable
			MAX-ACCESS read-write
			STATUS current
			DESCRIPTION
				"Black signal fail Trap Enable"
		::= { hsw3000c01v2Entry 204 }

		-- 1.3.6.1.4.1.10106.3.101291.1.1.205
		hsw3000c01v2In1FrzFail OBJECT-TYPE
			SYNTAX BitFail
			MAX-ACCESS read-only
			STATUS current
			DESCRIPTION
				"Freeze signal fail"
		::= { hsw3000c01v2Entry 205 }

		-- 1.3.6.1.4.1.10106.3.101291.1.1.206
		hsw3000c01v2In1FrzFailTrapEnable OBJECT-TYPE
			SYNTAX AlarmEnable
			MAX-ACCESS read-write
			STATUS current
			DESCRIPTION
				"Freeze signal fail Trap Enable"
		::= { hsw3000c01v2Entry 206 }

		-- 1.3.6.1.4.1.10106.3.101291.1.1.207
		hsw3000c01v2In1PatFail OBJECT-TYPE
			SYNTAX BitFail
			MAX-ACCESS read-only
			STATUS current
			DESCRIPTION
				"Video pattern fail"
		::= { hsw3000c01v2Entry 207 }

		-- 1.3.6.1.4.1.10106.3.101291.1.1.208
		hsw3000c01v2In1PatFailTrapEnable OBJECT-TYPE
			SYNTAX AlarmEnable
			MAX-ACCESS read-write
			STATUS current
			DESCRIPTION
				"Video pattern fail Trap Enable"
		::= { hsw3000c01v2Entry 208 }

		-- 1.3.6.1.4.1.10106.3.101291.1.1.209
		hsw3000c01v2In1CrcFail OBJECT-TYPE
			SYNTAX BitFail
			MAX-ACCESS read-only
			STATUS current
			DESCRIPTION
				"EDH/CRC fail"
		::= { hsw3000c01v2Entry 209 }

		-- 1.3.6.1.4.1.10106.3.101291.1.1.210
		hsw3000c01v2In1CrcFailTrapEnable OBJECT-TYPE
			SYNTAX AlarmEnable
			MAX-ACCESS read-write
			STATUS current
			DESCRIPTION
				"EDH/CRC fail Trap Enable"
		::= { hsw3000c01v2Entry 210 }

		-- 1.3.6.1.4.1.10106.3.101291.1.1.211
		hsw3000c01v2In1SilFail OBJECT-TYPE
			SYNTAX BitFail
			MAX-ACCESS read-only
			STATUS current
			DESCRIPTION
				"Audio silence fail"
		::= { hsw3000c01v2Entry 211 }

		-- 1.3.6.1.4.1.10106.3.101291.1.1.212
		hsw3000c01v2In1SilFailTrapEnable OBJECT-TYPE
			SYNTAX AlarmEnable
			MAX-ACCESS read-write
			STATUS current
			DESCRIPTION
				"Audio silence fail Trap Enable"
		::= { hsw3000c01v2Entry 212 }

		-- 1.3.6.1.4.1.10106.3.101291.1.1.213
		hsw3000c01v2In1OvrFail OBJECT-TYPE
			SYNTAX BitFail
			MAX-ACCESS read-only
			STATUS current
			DESCRIPTION
				"Audio overload fail"
		::= { hsw3000c01v2Entry 213 }

		-- 1.3.6.1.4.1.10106.3.101291.1.1.214
		hsw3000c01v2In1OvrFailTrapEnable OBJECT-TYPE
			SYNTAX AlarmEnable
			MAX-ACCESS read-write
			STATUS current
			DESCRIPTION
				"Audio overload fail Trap Enable"
		::= { hsw3000c01v2Entry 214 }

		-- 1.3.6.1.4.1.10106.3.101291.1.1.215
		hsw3000c01v2In1PhFail OBJECT-TYPE
			SYNTAX BitFail
			MAX-ACCESS read-only
			STATUS current
			DESCRIPTION
				"Audio phase fail"
		::= { hsw3000c01v2Entry 215 }

		-- 1.3.6.1.4.1.10106.3.101291.1.1.216
		hsw3000c01v2In1PhFailTrapEnable OBJECT-TYPE
			SYNTAX AlarmEnable
			MAX-ACCESS read-write
			STATUS current
			DESCRIPTION
				"Audio phase fail Trap Enable"
		::= { hsw3000c01v2Entry 216 }

		-- 1.3.6.1.4.1.10106.3.101291.1.1.217
		hsw3000c01v2In1PreFail OBJECT-TYPE
			SYNTAX BitFail
			MAX-ACCESS read-only
			STATUS current
			DESCRIPTION
				"Audio presence fail"
		::= { hsw3000c01v2Entry 217 }

		-- 1.3.6.1.4.1.10106.3.101291.1.1.218
		hsw3000c01v2In1PreFailTrapEnable OBJECT-TYPE
			SYNTAX AlarmEnable
			MAX-ACCESS read-write
			STATUS current
			DESCRIPTION
				"Audio presence fail Trap Enable"
		::= { hsw3000c01v2Entry 218 }

		-- 1.3.6.1.4.1.10106.3.101291.1.1.219
		hsw3000c01v2In2PhyFail OBJECT-TYPE
			SYNTAX BitFail
			MAX-ACCESS read-only
			STATUS current
			DESCRIPTION
				"Absence fail"
		::= { hsw3000c01v2Entry 219 }

		-- 1.3.6.1.4.1.10106.3.101291.1.1.220
		hsw3000c01v2In2PhyFailTrapEnable OBJECT-TYPE
			SYNTAX AlarmEnable
			MAX-ACCESS read-write
			STATUS current
			DESCRIPTION
				"Absence fail Trap Enable"
		::= { hsw3000c01v2Entry 220 }

		-- 1.3.6.1.4.1.10106.3.101291.1.1.221
		hsw3000c01v2In2FmtFail OBJECT-TYPE
			SYNTAX BitFail
			MAX-ACCESS read-only
			STATUS current
			DESCRIPTION
				"Format fail"
		::= { hsw3000c01v2Entry 221 }

		-- 1.3.6.1.4.1.10106.3.101291.1.1.222
		hsw3000c01v2In2FmtFailTrapEnable OBJECT-TYPE
			SYNTAX AlarmEnable
			MAX-ACCESS read-write
			STATUS current
			DESCRIPTION
				"Format fail Trap Enable"
		::= { hsw3000c01v2Entry 222 }

		-- 1.3.6.1.4.1.10106.3.101291.1.1.223
		hsw3000c01v2In2IncFail OBJECT-TYPE
			SYNTAX BitFail
			MAX-ACCESS read-only
			STATUS current
			DESCRIPTION
				"Incompatible format fail"
		::= { hsw3000c01v2Entry 223 }

		-- 1.3.6.1.4.1.10106.3.101291.1.1.224
		hsw3000c01v2In2IncFailTrapEnable OBJECT-TYPE
			SYNTAX AlarmEnable
			MAX-ACCESS read-write
			STATUS current
			DESCRIPTION
				"Incompatible format fail Trap Enable"
		::= { hsw3000c01v2Entry 224 }

		-- 1.3.6.1.4.1.10106.3.101291.1.1.225
		hsw3000c01v2In2GpiFail OBJECT-TYPE
			SYNTAX BitFail
			MAX-ACCESS read-only
			STATUS current
			DESCRIPTION
				"External GPI fail"
		::= { hsw3000c01v2Entry 225 }

		-- 1.3.6.1.4.1.10106.3.101291.1.1.226
		hsw3000c01v2In2GpiFailTrapEnable OBJECT-TYPE
			SYNTAX AlarmEnable
			MAX-ACCESS read-write
			STATUS current
			DESCRIPTION
				"External GPI fail Trap Enable"
		::= { hsw3000c01v2Entry 226 }

		-- 1.3.6.1.4.1.10106.3.101291.1.1.227
		hsw3000c01v2In2BlkFail OBJECT-TYPE
			SYNTAX BitFail
			MAX-ACCESS read-only
			STATUS current
			DESCRIPTION
				"Black signal fail"
		::= { hsw3000c01v2Entry 227 }

		-- 1.3.6.1.4.1.10106.3.101291.1.1.228
		hsw3000c01v2In2BlkFailTrapEnable OBJECT-TYPE
			SYNTAX AlarmEnable
			MAX-ACCESS read-write
			STATUS current
			DESCRIPTION
				"Black signal fail Trap Enable"
		::= { hsw3000c01v2Entry 228 }

		-- 1.3.6.1.4.1.10106.3.101291.1.1.229
		hsw3000c01v2In2FrzFail OBJECT-TYPE
			SYNTAX BitFail
			MAX-ACCESS read-only
			STATUS current
			DESCRIPTION
				"Freeze signal fail"
		::= { hsw3000c01v2Entry 229 }

		-- 1.3.6.1.4.1.10106.3.101291.1.1.230
		hsw3000c01v2In2FrzFailTrapEnable OBJECT-TYPE
			SYNTAX AlarmEnable
			MAX-ACCESS read-write
			STATUS current
			DESCRIPTION
				"Freeze signal fail Trap Enable"
		::= { hsw3000c01v2Entry 230 }

		-- 1.3.6.1.4.1.10106.3.101291.1.1.231
		hsw3000c01v2In2PatFail OBJECT-TYPE
			SYNTAX BitFail
			MAX-ACCESS read-only
			STATUS current
			DESCRIPTION
				"Video pattern fail"
		::= { hsw3000c01v2Entry 231 }

		-- 1.3.6.1.4.1.10106.3.101291.1.1.232
		hsw3000c01v2In2PatFailTrapEnable OBJECT-TYPE
			SYNTAX AlarmEnable
			MAX-ACCESS read-write
			STATUS current
			DESCRIPTION
				"Video pattern fail Trap Enable"
		::= { hsw3000c01v2Entry 232 }

		-- 1.3.6.1.4.1.10106.3.101291.1.1.233
		hsw3000c01v2In2CrcFail OBJECT-TYPE
			SYNTAX BitFail
			MAX-ACCESS read-only
			STATUS current
			DESCRIPTION
				"EDH/CRC fail"
		::= { hsw3000c01v2Entry 233 }

		-- 1.3.6.1.4.1.10106.3.101291.1.1.234
		hsw3000c01v2In2CrcFailTrapEnable OBJECT-TYPE
			SYNTAX AlarmEnable
			MAX-ACCESS read-write
			STATUS current
			DESCRIPTION
				"EDH/CRC fail Trap Enable"
		::= { hsw3000c01v2Entry 234 }

		-- 1.3.6.1.4.1.10106.3.101291.1.1.235
		hsw3000c01v2In2SilFail OBJECT-TYPE
			SYNTAX BitFail
			MAX-ACCESS read-only
			STATUS current
			DESCRIPTION
				"Audio silence fail"
		::= { hsw3000c01v2Entry 235 }

		-- 1.3.6.1.4.1.10106.3.101291.1.1.236
		hsw3000c01v2In2SilFailTrapEnable OBJECT-TYPE
			SYNTAX AlarmEnable
			MAX-ACCESS read-write
			STATUS current
			DESCRIPTION
				"Audio silence fail Trap Enable"
		::= { hsw3000c01v2Entry 236 }

		-- 1.3.6.1.4.1.10106.3.101291.1.1.237
		hsw3000c01v2In2OvrFail OBJECT-TYPE
			SYNTAX BitFail
			MAX-ACCESS read-only
			STATUS current
			DESCRIPTION
				"Audio overload fail"
		::= { hsw3000c01v2Entry 237 }

		-- 1.3.6.1.4.1.10106.3.101291.1.1.238
		hsw3000c01v2In2OvrFailTrapEnable OBJECT-TYPE
			SYNTAX AlarmEnable
			MAX-ACCESS read-write
			STATUS current
			DESCRIPTION
				"Audio overload fail Trap Enable"
		::= { hsw3000c01v2Entry 238 }

		-- 1.3.6.1.4.1.10106.3.101291.1.1.239
		hsw3000c01v2In2PhFail OBJECT-TYPE
			SYNTAX BitFail
			MAX-ACCESS read-only
			STATUS current
			DESCRIPTION
				"Audio phase fail"
		::= { hsw3000c01v2Entry 239 }

		-- 1.3.6.1.4.1.10106.3.101291.1.1.240
		hsw3000c01v2In2PhFailTrapEnable OBJECT-TYPE
			SYNTAX AlarmEnable
			MAX-ACCESS read-write
			STATUS current
			DESCRIPTION
				"Audio phase fail Trap Enable"
		::= { hsw3000c01v2Entry 240 }

		-- 1.3.6.1.4.1.10106.3.101291.1.1.241
		hsw3000c01v2In2PreFail OBJECT-TYPE
			SYNTAX BitFail
			MAX-ACCESS read-only
			STATUS current
			DESCRIPTION
				"Audio presence fail"
		::= { hsw3000c01v2Entry 241 }

		-- 1.3.6.1.4.1.10106.3.101291.1.1.242
		hsw3000c01v2In2PreFailTrapEnable OBJECT-TYPE
			SYNTAX AlarmEnable
			MAX-ACCESS read-write
			STATUS current
			DESCRIPTION
				"Audio presence fail Trap Enable"
		::= { hsw3000c01v2Entry 242 }

		-- 1.3.6.1.4.1.10106.3.101291.1.1.243
		hsw3000c01v2RefFail OBJECT-TYPE
			SYNTAX BitFail
			MAX-ACCESS read-only
			STATUS current
			DESCRIPTION
				"Reference absence fail"
		::= { hsw3000c01v2Entry 243 }

		-- 1.3.6.1.4.1.10106.3.101291.1.1.244
		hsw3000c01v2RefFailTrapEnable OBJECT-TYPE
			SYNTAX AlarmEnable
			MAX-ACCESS read-write
			STATUS current
			DESCRIPTION
				"Reference absence fail Trap Enable"
		::= { hsw3000c01v2Entry 244 }

		-- 1.3.6.1.4.1.10106.3.101291.1.1.245
		hsw3000c01v2LockFail OBJECT-TYPE
			SYNTAX BitFail
			MAX-ACCESS read-only
			STATUS current
			DESCRIPTION
				"Reference unlock fail"
		::= { hsw3000c01v2Entry 245 }

		-- 1.3.6.1.4.1.10106.3.101291.1.1.246
		hsw3000c01v2LockFailTrapEnable OBJECT-TYPE
			SYNTAX AlarmEnable
			MAX-ACCESS read-write
			STATUS current
			DESCRIPTION
				"Reference unlock fail Trap Enable"
		::= { hsw3000c01v2Entry 246 }

		-- 1.3.6.1.4.1.10106.3.101291.1.1.247
		hsw3000c01v2BliGpiFail OBJECT-TYPE
			SYNTAX BitFail
			MAX-ACCESS read-only
			STATUS current
			DESCRIPTION
				"GPI2B status (used in blind halfauto mode)"
		::= { hsw3000c01v2Entry 247 }

		-- 1.3.6.1.4.1.10106.3.101291.1.1.249
		hsw3000c01v2In1Format OBJECT-TYPE
			SYNTAX SdiHd3gFmt3
			MAX-ACCESS read-only
			STATUS current
			DESCRIPTION
				"Input format"
		::= { hsw3000c01v2Entry 249 }

		-- 1.3.6.1.4.1.10106.3.101291.1.1.250
		hsw3000c01v2In1FormatTrapEnable OBJECT-TYPE
			SYNTAX AlarmEnable
			MAX-ACCESS read-write
			STATUS current
			DESCRIPTION
				"Input format Trap Enable"
		::= { hsw3000c01v2Entry 250 }

		-- 1.3.6.1.4.1.10106.3.101291.1.1.251
		hsw3000c01v2In2Format OBJECT-TYPE
			SYNTAX SdiHd3gFmt3
			MAX-ACCESS read-only
			STATUS current
			DESCRIPTION
				"Input format"
		::= { hsw3000c01v2Entry 251 }

		-- 1.3.6.1.4.1.10106.3.101291.1.1.252
		hsw3000c01v2In2FormatTrapEnable OBJECT-TYPE
			SYNTAX AlarmEnable
			MAX-ACCESS read-write
			STATUS current
			DESCRIPTION
				"Input format Trap Enable"
		::= { hsw3000c01v2Entry 252 }

		-- 1.3.6.1.4.1.10106.3.101291.1.1.253
		hsw3000c01v2RefFormat OBJECT-TYPE
			SYNTAX SdiHd3gFmt3
			MAX-ACCESS read-only
			STATUS current
			DESCRIPTION
				"Reference format"
		::= { hsw3000c01v2Entry 253 }

		-- 1.3.6.1.4.1.10106.3.101291.1.1.254
		hsw3000c01v2RefFormatTrapEnable OBJECT-TYPE
			SYNTAX AlarmEnable
			MAX-ACCESS read-write
			STATUS current
			DESCRIPTION
				"Reference format Trap Enable"
		::= { hsw3000c01v2Entry 254 }

		-- 1.3.6.1.4.1.10106.3.101291.1.1.255
		hsw3000c01v2SerialNo OBJECT-TYPE
			SYNTAX SerialNo
			MAX-ACCESS read-only
			STATUS current
			DESCRIPTION
				"Serial number"
		::= { hsw3000c01v2Entry 255 }

		-- 1.3.6.1.4.1.10106.3.101291.1.1.257
		hsw3000c01v2SynchroModeIn1 OBJECT-TYPE
			SYNTAX Bit0Fra1Lin
			MAX-ACCESS read-write
			STATUS current
			DESCRIPTION
				"Allows selecting the synchronizing mode"
		::= { hsw3000c01v2Entry 257 }

		-- 1.3.6.1.4.1.10106.3.101291.1.1.259
		hsw3000c01v2SynchroModeIn2 OBJECT-TYPE
			SYNTAX Bit0Fra1Lin
			MAX-ACCESS read-write
			STATUS current
			DESCRIPTION
				"Allows selecting the synchronizing mode"
		::= { hsw3000c01v2Entry 259 }

		-- 1.3.6.1.4.1.10106.3.101291.1.1.261
		hsw3000c01v2StatusMode OBJECT-TYPE
			SYNTAX StatusMode
			MAX-ACCESS read-write
			STATUS current
			DESCRIPTION
				"Allows selecting if status informaction is afected by activation/desactivation timing"
		::= { hsw3000c01v2Entry 261 }

		-- 1.3.6.1.4.1.10106.3.101291.1.1.263
		hsw3000c01v2EqualPid OBJECT-TYPE
			SYNTAX UmidStatus
			MAX-ACCESS read-only
			STATUS current
			DESCRIPTION
				"Indicates if both  inputs have same PID"
		::= { hsw3000c01v2Entry 263 }

		-- 1.3.6.1.4.1.10106.3.101291.1.1.264
		hsw3000c01v2EqualPidTrapEnable OBJECT-TYPE
			SYNTAX AlarmEnable
			MAX-ACCESS read-write
			STATUS current
			DESCRIPTION
				"Indicates if both  inputs have same PID Trap Enable"
		::= { hsw3000c01v2Entry 264 }

		-- 1.3.6.1.4.1.10106.3.101291.1.1.265
		hsw3000c01v2EqualUmid OBJECT-TYPE
			SYNTAX UmidStatus
			MAX-ACCESS read-only
			STATUS current
			DESCRIPTION
				"Indicates if both  inputs have same UMID"
		::= { hsw3000c01v2Entry 265 }

		-- 1.3.6.1.4.1.10106.3.101291.1.1.266
		hsw3000c01v2EqualUmidTrapEnable OBJECT-TYPE
			SYNTAX AlarmEnable
			MAX-ACCESS read-write
			STATUS current
			DESCRIPTION
				"Indicates if both  inputs have same UMID Trap Enable"
		::= { hsw3000c01v2Entry 266 }

		-- 1.3.6.1.4.1.10106.3.101291.1.1.267
		hsw3000c01v2In1PidPres OBJECT-TYPE
			SYNTAX Bit0No1Yes
			MAX-ACCESS read-only
			STATUS current
			DESCRIPTION
				"Indicates if there are PID packets"
		::= { hsw3000c01v2Entry 267 }

		-- 1.3.6.1.4.1.10106.3.101291.1.1.269
		hsw3000c01v2In2PidPres OBJECT-TYPE
			SYNTAX Bit0No1Yes
			MAX-ACCESS read-only
			STATUS current
			DESCRIPTION
				"Indicates if there are PID packets"
		::= { hsw3000c01v2Entry 269 }

		-- 1.3.6.1.4.1.10106.3.101291.1.1.271
		hsw3000c01v2In1UmidPres OBJECT-TYPE
			SYNTAX Bit0No1Yes
			MAX-ACCESS read-only
			STATUS current
			DESCRIPTION
				"Indicates if there are UMID packets"
		::= { hsw3000c01v2Entry 271 }

		-- 1.3.6.1.4.1.10106.3.101291.1.1.273
		hsw3000c01v2In2UmidPres OBJECT-TYPE
			SYNTAX Bit0No1Yes
			MAX-ACCESS read-only
			STATUS current
			DESCRIPTION
				"Indicates if there are UMID packets"
		::= { hsw3000c01v2Entry 273 }

		-- 1.3.6.1.4.1.10106.3.101291.1.1.275
		hsw3000c01v2In1Grp1Pres OBJECT-TYPE
			SYNTAX Bit0No1Yes
			MAX-ACCESS read-only
			STATUS current
			DESCRIPTION
				"Audio group 1 packet presence"
		::= { hsw3000c01v2Entry 275 }

		-- 1.3.6.1.4.1.10106.3.101291.1.1.276
		hsw3000c01v2In1Grp1PresTrapEnable OBJECT-TYPE
			SYNTAX AlarmEnable
			MAX-ACCESS read-write
			STATUS current
			DESCRIPTION
				"Audio group 1 packet presence Trap Enable"
		::= { hsw3000c01v2Entry 276 }

		-- 1.3.6.1.4.1.10106.3.101291.1.1.277
		hsw3000c01v2In1Grp2Pres OBJECT-TYPE
			SYNTAX Bit0No1Yes
			MAX-ACCESS read-only
			STATUS current
			DESCRIPTION
				"Audio group 2 packet presence"
		::= { hsw3000c01v2Entry 277 }

		-- 1.3.6.1.4.1.10106.3.101291.1.1.278
		hsw3000c01v2In1Grp2PresTrapEnable OBJECT-TYPE
			SYNTAX AlarmEnable
			MAX-ACCESS read-write
			STATUS current
			DESCRIPTION
				"Audio group 2 packet presence Trap Enable"
		::= { hsw3000c01v2Entry 278 }

		-- 1.3.6.1.4.1.10106.3.101291.1.1.279
		hsw3000c01v2In1Grp3Pres OBJECT-TYPE
			SYNTAX Bit0No1Yes
			MAX-ACCESS read-only
			STATUS current
			DESCRIPTION
				"Audio group 3 packet presence"
		::= { hsw3000c01v2Entry 279 }

		-- 1.3.6.1.4.1.10106.3.101291.1.1.280
		hsw3000c01v2In1Grp3PresTrapEnable OBJECT-TYPE
			SYNTAX AlarmEnable
			MAX-ACCESS read-write
			STATUS current
			DESCRIPTION
				"Audio group 3 packet presence Trap Enable"
		::= { hsw3000c01v2Entry 280 }

		-- 1.3.6.1.4.1.10106.3.101291.1.1.281
		hsw3000c01v2In1Grp4Pres OBJECT-TYPE
			SYNTAX Bit0No1Yes
			MAX-ACCESS read-only
			STATUS current
			DESCRIPTION
				"Audio group 4 packet presence"
		::= { hsw3000c01v2Entry 281 }

		-- 1.3.6.1.4.1.10106.3.101291.1.1.282
		hsw3000c01v2In1Grp4PresTrapEnable OBJECT-TYPE
			SYNTAX AlarmEnable
			MAX-ACCESS read-write
			STATUS current
			DESCRIPTION
				"Audio group 4 packet presence Trap Enable"
		::= { hsw3000c01v2Entry 282 }

		-- 1.3.6.1.4.1.10106.3.101291.1.1.283
		hsw3000c01v2In1Grp1P0Err OBJECT-TYPE
			SYNTAX BitFail
			MAX-ACCESS read-only
			STATUS current
			DESCRIPTION
				"Audio group 1 pair 0 fail"
		::= { hsw3000c01v2Entry 283 }

		-- 1.3.6.1.4.1.10106.3.101291.1.1.284
		hsw3000c01v2In1Grp1P0ErrTrapEnable OBJECT-TYPE
			SYNTAX AlarmEnable
			MAX-ACCESS read-write
			STATUS current
			DESCRIPTION
				"Audio group 1 pair 0 fail Trap Enable"
		::= { hsw3000c01v2Entry 284 }

		-- 1.3.6.1.4.1.10106.3.101291.1.1.285
		hsw3000c01v2In1Grp1P1Err OBJECT-TYPE
			SYNTAX BitFail
			MAX-ACCESS read-only
			STATUS current
			DESCRIPTION
				"Audio group 1 pair 1 fail"
		::= { hsw3000c01v2Entry 285 }

		-- 1.3.6.1.4.1.10106.3.101291.1.1.286
		hsw3000c01v2In1Grp1P1ErrTrapEnable OBJECT-TYPE
			SYNTAX AlarmEnable
			MAX-ACCESS read-write
			STATUS current
			DESCRIPTION
				"Audio group 1 pair 1 fail Trap Enable"
		::= { hsw3000c01v2Entry 286 }

		-- 1.3.6.1.4.1.10106.3.101291.1.1.287
		hsw3000c01v2In1Grp2P0Err OBJECT-TYPE
			SYNTAX BitFail
			MAX-ACCESS read-only
			STATUS current
			DESCRIPTION
				"Audio group 2 pair 0 fail"
		::= { hsw3000c01v2Entry 287 }

		-- 1.3.6.1.4.1.10106.3.101291.1.1.288
		hsw3000c01v2In1Grp2P0ErrTrapEnable OBJECT-TYPE
			SYNTAX AlarmEnable
			MAX-ACCESS read-write
			STATUS current
			DESCRIPTION
				"Audio group 2 pair 0 fail Trap Enable"
		::= { hsw3000c01v2Entry 288 }

		-- 1.3.6.1.4.1.10106.3.101291.1.1.289
		hsw3000c01v2In1Grp2P1Err OBJECT-TYPE
			SYNTAX BitFail
			MAX-ACCESS read-only
			STATUS current
			DESCRIPTION
				"Audio group 2 pair 1 fail"
		::= { hsw3000c01v2Entry 289 }

		-- 1.3.6.1.4.1.10106.3.101291.1.1.290
		hsw3000c01v2In1Grp2P1ErrTrapEnable OBJECT-TYPE
			SYNTAX AlarmEnable
			MAX-ACCESS read-write
			STATUS current
			DESCRIPTION
				"Audio group 2 pair 1 fail Trap Enable"
		::= { hsw3000c01v2Entry 290 }

		-- 1.3.6.1.4.1.10106.3.101291.1.1.291
		hsw3000c01v2In1Grp3P0Err OBJECT-TYPE
			SYNTAX BitFail
			MAX-ACCESS read-only
			STATUS current
			DESCRIPTION
				"Audio group 3 pair 0 fail"
		::= { hsw3000c01v2Entry 291 }

		-- 1.3.6.1.4.1.10106.3.101291.1.1.292
		hsw3000c01v2In1Grp3P0ErrTrapEnable OBJECT-TYPE
			SYNTAX AlarmEnable
			MAX-ACCESS read-write
			STATUS current
			DESCRIPTION
				"Audio group 3 pair 0 fail Trap Enable"
		::= { hsw3000c01v2Entry 292 }

		-- 1.3.6.1.4.1.10106.3.101291.1.1.293
		hsw3000c01v2In1Grp3P1Err OBJECT-TYPE
			SYNTAX BitFail
			MAX-ACCESS read-only
			STATUS current
			DESCRIPTION
				"Audio group 3 pair 1 fail"
		::= { hsw3000c01v2Entry 293 }

		-- 1.3.6.1.4.1.10106.3.101291.1.1.294
		hsw3000c01v2In1Grp3P1ErrTrapEnable OBJECT-TYPE
			SYNTAX AlarmEnable
			MAX-ACCESS read-write
			STATUS current
			DESCRIPTION
				"Audio group 3 pair 1 fail Trap Enable"
		::= { hsw3000c01v2Entry 294 }

		-- 1.3.6.1.4.1.10106.3.101291.1.1.295
		hsw3000c01v2In1Grp4P0Err OBJECT-TYPE
			SYNTAX BitFail
			MAX-ACCESS read-only
			STATUS current
			DESCRIPTION
				"Audio group 4 pair 0 fail"
		::= { hsw3000c01v2Entry 295 }

		-- 1.3.6.1.4.1.10106.3.101291.1.1.296
		hsw3000c01v2In1Grp4P0ErrTrapEnable OBJECT-TYPE
			SYNTAX AlarmEnable
			MAX-ACCESS read-write
			STATUS current
			DESCRIPTION
				"Audio group 4 pair 0 fail Trap Enable"
		::= { hsw3000c01v2Entry 296 }

		-- 1.3.6.1.4.1.10106.3.101291.1.1.297
		hsw3000c01v2In1Grp4P1Err OBJECT-TYPE
			SYNTAX BitFail
			MAX-ACCESS read-only
			STATUS current
			DESCRIPTION
				"Audio group 4 pair 1 fail"
		::= { hsw3000c01v2Entry 297 }

		-- 1.3.6.1.4.1.10106.3.101291.1.1.298
		hsw3000c01v2In1Grp4P1ErrTrapEnable OBJECT-TYPE
			SYNTAX AlarmEnable
			MAX-ACCESS read-write
			STATUS current
			DESCRIPTION
				"Audio group 4 pair 1 fail Trap Enable"
		::= { hsw3000c01v2Entry 298 }

		-- 1.3.6.1.4.1.10106.3.101291.1.1.299
		hsw3000c01v2In2Grp1Pres OBJECT-TYPE
			SYNTAX Bit0No1Yes
			MAX-ACCESS read-only
			STATUS current
			DESCRIPTION
				"Audio group 1 packet presence"
		::= { hsw3000c01v2Entry 299 }

		-- 1.3.6.1.4.1.10106.3.101291.1.1.300
		hsw3000c01v2In2Grp1PresTrapEnable OBJECT-TYPE
			SYNTAX AlarmEnable
			MAX-ACCESS read-write
			STATUS current
			DESCRIPTION
				"Audio group 1 packet presence Trap Enable"
		::= { hsw3000c01v2Entry 300 }

		-- 1.3.6.1.4.1.10106.3.101291.1.1.301
		hsw3000c01v2In2Grp2Pres OBJECT-TYPE
			SYNTAX Bit0No1Yes
			MAX-ACCESS read-only
			STATUS current
			DESCRIPTION
				"Audio group 2 packet presence"
		::= { hsw3000c01v2Entry 301 }

		-- 1.3.6.1.4.1.10106.3.101291.1.1.302
		hsw3000c01v2In2Grp2PresTrapEnable OBJECT-TYPE
			SYNTAX AlarmEnable
			MAX-ACCESS read-write
			STATUS current
			DESCRIPTION
				"Audio group 2 packet presence Trap Enable"
		::= { hsw3000c01v2Entry 302 }

		-- 1.3.6.1.4.1.10106.3.101291.1.1.303
		hsw3000c01v2In2Grp3Pres OBJECT-TYPE
			SYNTAX Bit0No1Yes
			MAX-ACCESS read-only
			STATUS current
			DESCRIPTION
				"Audio group 3 packet presence"
		::= { hsw3000c01v2Entry 303 }

		-- 1.3.6.1.4.1.10106.3.101291.1.1.304
		hsw3000c01v2In2Grp3PresTrapEnable OBJECT-TYPE
			SYNTAX AlarmEnable
			MAX-ACCESS read-write
			STATUS current
			DESCRIPTION
				"Audio group 3 packet presence Trap Enable"
		::= { hsw3000c01v2Entry 304 }

		-- 1.3.6.1.4.1.10106.3.101291.1.1.305
		hsw3000c01v2In2Grp4Pres OBJECT-TYPE
			SYNTAX Bit0No1Yes
			MAX-ACCESS read-only
			STATUS current
			DESCRIPTION
				"Audio group 4 packet presence"
		::= { hsw3000c01v2Entry 305 }

		-- 1.3.6.1.4.1.10106.3.101291.1.1.306
		hsw3000c01v2In2Grp4PresTrapEnable OBJECT-TYPE
			SYNTAX AlarmEnable
			MAX-ACCESS read-write
			STATUS current
			DESCRIPTION
				"Audio group 4 packet presence Trap Enable"
		::= { hsw3000c01v2Entry 306 }

		-- 1.3.6.1.4.1.10106.3.101291.1.1.307
		hsw3000c01v2In2Grp1P0Err OBJECT-TYPE
			SYNTAX BitFail
			MAX-ACCESS read-only
			STATUS current
			DESCRIPTION
				"Audio group 1 pair 0 fail"
		::= { hsw3000c01v2Entry 307 }

		-- 1.3.6.1.4.1.10106.3.101291.1.1.308
		hsw3000c01v2In2Grp1P0ErrTrapEnable OBJECT-TYPE
			SYNTAX AlarmEnable
			MAX-ACCESS read-write
			STATUS current
			DESCRIPTION
				"Audio group 1 pair 0 fail Trap Enable"
		::= { hsw3000c01v2Entry 308 }

		-- 1.3.6.1.4.1.10106.3.101291.1.1.309
		hsw3000c01v2In2Grp1P1Err OBJECT-TYPE
			SYNTAX BitFail
			MAX-ACCESS read-only
			STATUS current
			DESCRIPTION
				"Audio group 1 pair 1 fail"
		::= { hsw3000c01v2Entry 309 }

		-- 1.3.6.1.4.1.10106.3.101291.1.1.310
		hsw3000c01v2In2Grp1P1ErrTrapEnable OBJECT-TYPE
			SYNTAX AlarmEnable
			MAX-ACCESS read-write
			STATUS current
			DESCRIPTION
				"Audio group 1 pair 1 fail Trap Enable"
		::= { hsw3000c01v2Entry 310 }

		-- 1.3.6.1.4.1.10106.3.101291.1.1.311
		hsw3000c01v2In2Grp2P0Err OBJECT-TYPE
			SYNTAX BitFail
			MAX-ACCESS read-only
			STATUS current
			DESCRIPTION
				"Audio group 2 pair 0 fail"
		::= { hsw3000c01v2Entry 311 }

		-- 1.3.6.1.4.1.10106.3.101291.1.1.312
		hsw3000c01v2In2Grp2P0ErrTrapEnable OBJECT-TYPE
			SYNTAX AlarmEnable
			MAX-ACCESS read-write
			STATUS current
			DESCRIPTION
				"Audio group 2 pair 0 fail Trap Enable"
		::= { hsw3000c01v2Entry 312 }

		-- 1.3.6.1.4.1.10106.3.101291.1.1.313
		hsw3000c01v2In2Grp2P1Err OBJECT-TYPE
			SYNTAX BitFail
			MAX-ACCESS read-only
			STATUS current
			DESCRIPTION
				"Audio group 2 pair 1 fail"
		::= { hsw3000c01v2Entry 313 }

		-- 1.3.6.1.4.1.10106.3.101291.1.1.314
		hsw3000c01v2In2Grp2P1ErrTrapEnable OBJECT-TYPE
			SYNTAX AlarmEnable
			MAX-ACCESS read-write
			STATUS current
			DESCRIPTION
				"Audio group 2 pair 1 fail Trap Enable"
		::= { hsw3000c01v2Entry 314 }

		-- 1.3.6.1.4.1.10106.3.101291.1.1.315
		hsw3000c01v2In2Grp3P0Err OBJECT-TYPE
			SYNTAX BitFail
			MAX-ACCESS read-only
			STATUS current
			DESCRIPTION
				"Audio group 3 pair 0 fail"
		::= { hsw3000c01v2Entry 315 }

		-- 1.3.6.1.4.1.10106.3.101291.1.1.316
		hsw3000c01v2In2Grp3P0ErrTrapEnable OBJECT-TYPE
			SYNTAX AlarmEnable
			MAX-ACCESS read-write
			STATUS current
			DESCRIPTION
				"Audio group 3 pair 0 fail Trap Enable"
		::= { hsw3000c01v2Entry 316 }

		-- 1.3.6.1.4.1.10106.3.101291.1.1.317
		hsw3000c01v2In2Grp3P1Err OBJECT-TYPE
			SYNTAX BitFail
			MAX-ACCESS read-only
			STATUS current
			DESCRIPTION
				"Audio group 3 pair 1 fail"
		::= { hsw3000c01v2Entry 317 }

		-- 1.3.6.1.4.1.10106.3.101291.1.1.318
		hsw3000c01v2In2Grp3P1ErrTrapEnable OBJECT-TYPE
			SYNTAX AlarmEnable
			MAX-ACCESS read-write
			STATUS current
			DESCRIPTION
				"Audio group 3 pair 1 fail Trap Enable"
		::= { hsw3000c01v2Entry 318 }

		-- 1.3.6.1.4.1.10106.3.101291.1.1.319
		hsw3000c01v2In2Grp4P0Err OBJECT-TYPE
			SYNTAX BitFail
			MAX-ACCESS read-only
			STATUS current
			DESCRIPTION
				"Audio group 4 pair 0 fail"
		::= { hsw3000c01v2Entry 319 }

		-- 1.3.6.1.4.1.10106.3.101291.1.1.320
		hsw3000c01v2In2Grp4P0ErrTrapEnable OBJECT-TYPE
			SYNTAX AlarmEnable
			MAX-ACCESS read-write
			STATUS current
			DESCRIPTION
				"Audio group 4 pair 0 fail Trap Enable"
		::= { hsw3000c01v2Entry 320 }

		-- 1.3.6.1.4.1.10106.3.101291.1.1.321
		hsw3000c01v2In2Grp4P1Err OBJECT-TYPE
			SYNTAX BitFail
			MAX-ACCESS read-only
			STATUS current
			DESCRIPTION
				"Audio group 4 pair 1 fail"
		::= { hsw3000c01v2Entry 321 }

		-- 1.3.6.1.4.1.10106.3.101291.1.1.322
		hsw3000c01v2In2Grp4P1ErrTrapEnable OBJECT-TYPE
			SYNTAX AlarmEnable
			MAX-ACCESS read-write
			STATUS current
			DESCRIPTION
				"Audio group 4 pair 1 fail Trap Enable"
		::= { hsw3000c01v2Entry 322 }

		-- 1.3.6.1.4.1.10106.3.364803
		hsw3000c01v3 OBJECT IDENTIFIER ::= { albalaProducts 364803 }

		-- 1.3.6.1.4.1.10106.3.364803.1
		hsw3000c01v3Table  OBJECT-TYPE
			SYNTAX SEQUENCE OF Hsw3000c01v3Entry
			MAX-ACCESS not-accessible
			STATUS current
			DESCRIPTION
				"Module  HSW3000C01V3 Table"
			::= { hsw3000c01v3 1 }

		-- 1.3.6.1.4.1.10106.3.364803.1.1
		hsw3000c01v3Entry  OBJECT-TYPE
			SYNTAX Hsw3000c01v3Entry
			MAX-ACCESS not-accessible
			STATUS current
			DESCRIPTION
				"Module HSW3000C01V3 Entry"
			INDEX { hsw3000c01v3Index }
			::= { hsw3000c01v3Table 1 }

			Hsw3000c01v3Entry ::=
			SEQUENCE {
				hsw3000c01v3Index
				ModuleIndex,
				hsw3000c01v3ActivePreset
				PresetActive,
				hsw3000c01v3LoadPreset
				PresetLoad,
				hsw3000c01v3SavePreset
				PresetSave,
				hsw3000c01v3StateSel
				HswState,
				hsw3000c01v3StateSelTrapEnable
				AlarmEnable,
				hsw3000c01v3SwitchMode
				HswSwMode,
				hsw3000c01v3SwitchModeTrapEnable
				AlarmEnable,
				hsw3000c01v3FreezeMode
				HswFreezeMode,
				hsw3000c01v3BypassEnable
				Bit0Dis1Ena,
				hsw3000c01v3BypassEnableTrapEnable
				AlarmEnable,
				hsw3000c01v3InpFailMode
				Bit0No1Yes,
				hsw3000c01v3OperatingMode
				HswOperMode,
				hsw3000c01v3OperatingModeTrapEnable
				AlarmEnable,
				hsw3000c01v3StateAMap
				HswMapState,
				hsw3000c01v3StateBMap
				HswMapState,
				hsw3000c01v3StateAGpo
				HswGpoState,
				hsw3000c01v3StateBGpo
				HswGpoState,
				hsw3000c01v3AnaRefFmt
				SdiHd3gFmt5,
				hsw3000c01v3In1StChange
				Bit0No1Yes,
				hsw3000c01v3In2StChange
				Bit0No1Yes,
				hsw3000c01v3Gpi1StChange
				Bit0No1Yes,
				hsw3000c01v3Gpi2StChange
				Bit0No1Yes,
				hsw3000c01v3Gpi3StChange
				Bit0No1Yes,
				hsw3000c01v3InputChange
				Bit0No1Yes,
				hsw3000c01v3VDelay
				DelayLines2,
				hsw3000c01v3HDelay
				DelayPixel5,
				hsw3000c01v3Holdoff
				TimeS2,
				hsw3000c01v3PhyFailTim
				HswTiming,
				hsw3000c01v3FmtFailTim
				HswTiming,
				hsw3000c01v3IncFailTim
				HswTiming,
				hsw3000c01v3StatusMode
				StatusMode,
				hsw3000c01v3SynchroModeIn1
				Bit0Fra1Lin,
				hsw3000c01v3SynchroModeIn2
				Bit0Fra1Lin,
				hsw3000c01v3GpiFailTim
				HswTiming,
				hsw3000c01v3BlkFailTim
				HswTiming,
				hsw3000c01v3FrzFailTim
				HswTiming,
				hsw3000c01v3PatFailTim
				HswTiming,
				hsw3000c01v3CrcFailTim
				HswTiming,
				hsw3000c01v3SilFailTim
				HswTiming,
				hsw3000c01v3OvrFailTim
				HswTiming,
				hsw3000c01v3PhFailTim
				HswTiming,
				hsw3000c01v3PresFailTim
				HswTiming,
				hsw3000c01v3ActPer1
				TimeS2,
				hsw3000c01v3DeactPer1
				TimeS2,
				hsw3000c01v3ActPer2
				TimeS2,
				hsw3000c01v3DeactPer2
				TimeS2,
				hsw3000c01v3CrcThreshold
				Rate2,
				hsw3000c01v3BlackThreshold
				BlackThreshold,
				hsw3000c01v3VertFrozenWin
				Rate1,
				hsw3000c01v3HtalFrozenWin
				Rate1,
				hsw3000c01v3In1PhyFailMsk
				BitMask,
				hsw3000c01v3In1FmtFailMsk
				BitMask,
				hsw3000c01v3In1IncFailMsk
				BitMask,
				hsw3000c01v3In1GpiFailMsk
				BitMask,
				hsw3000c01v3In1BlkFailMsk
				BitMask,
				hsw3000c01v3In1FrzFailMsk
				BitMask,
				hsw3000c01v3In1PatFailMsk
				BitMask,
				hsw3000c01v3In1CrcFailMsk
				BitMask,
				hsw3000c01v3In1SilFailMsk
				BitMask,
				hsw3000c01v3In1OvrFailMsk
				BitMask,
				hsw3000c01v3In1PhFailMsk
				BitMask,
				hsw3000c01v3In1PreFailMsk
				BitMask,
				hsw3000c01v3In2PhyFailMsk
				BitMask,
				hsw3000c01v3In2FmtFailMsk
				BitMask,
				hsw3000c01v3In2IncFailMsk
				BitMask,
				hsw3000c01v3In2GpiFailMsk
				BitMask,
				hsw3000c01v3In2BlkFailMsk
				BitMask,
				hsw3000c01v3In2FrzFailMsk
				BitMask,
				hsw3000c01v3In2PatFailMsk
				BitMask,
				hsw3000c01v3In2CrcFailMsk
				BitMask,
				hsw3000c01v3In2SilFailMsk
				BitMask,
				hsw3000c01v3In2OvrFailMsk
				BitMask,
				hsw3000c01v3In2PhFailMsk
				BitMask,
				hsw3000c01v3In2PreFailMsk
				BitMask,
				hsw3000c01v3RefFailMsk
				BitMask,
				hsw3000c01v3LockFailMsk
				BitMask,
				hsw3000c01v3In1AudG1p0Msk
				AudioMask,
				hsw3000c01v3In1AudG1p1Msk
				AudioMask,
				hsw3000c01v3In1AudG2p0Msk
				AudioMask,
				hsw3000c01v3In1AudG2p1Msk
				AudioMask,
				hsw3000c01v3In1AudG3p0Msk
				AudioMask,
				hsw3000c01v3In1AudG3p1Msk
				AudioMask,
				hsw3000c01v3In1AudG4p0Msk
				AudioMask,
				hsw3000c01v3In1AudG4p1Msk
				AudioMask,
				hsw3000c01v3In2AudG1p0Msk
				AudioMask,
				hsw3000c01v3In2AudG1p1Msk
				AudioMask,
				hsw3000c01v3In2AudG2p0Msk
				AudioMask,
				hsw3000c01v3In2AudG2p1Msk
				AudioMask,
				hsw3000c01v3In2AudG3p0Msk
				AudioMask,
				hsw3000c01v3In2AudG3p1Msk
				AudioMask,
				hsw3000c01v3In2AudG4p0Msk
				AudioMask,
				hsw3000c01v3In2AudG4p1Msk
				AudioMask,
				hsw3000c01v3SilenceLevel
				LevelDbfs3,
				hsw3000c01v3SilenceTime
				TimeS2,
				hsw3000c01v3OverloadLevel
				LevelDbfs4,
				hsw3000c01v3TxtLinesThrs
				TxtThreshold,
				hsw3000c01v3In1Fail
				BitFail,
				hsw3000c01v3In1FailTrapEnable
				AlarmEnable,
				hsw3000c01v3In2Fail
				BitFail,
				hsw3000c01v3In2FailTrapEnable
				AlarmEnable,
				hsw3000c01v3In1ExtFail
				BitFail,
				hsw3000c01v3In1ExtFailTrapEnable
				AlarmEnable,
				hsw3000c01v3In2ExtFail
				BitFail,
				hsw3000c01v3In2ExtFailTrapEnable
				AlarmEnable,
				hsw3000c01v3BlindExtFail
				BitFail,
				hsw3000c01v3BlindExtFailTrapEnable
				AlarmEnable,
				hsw3000c01v3EqualPid
				UmidStatus,
				hsw3000c01v3EqualPidTrapEnable
				AlarmEnable,
				hsw3000c01v3SelOut1
				HswOutput,
				hsw3000c01v3SelOut1TrapEnable
				AlarmEnable,
				hsw3000c01v3SelOut2
				HswOutput,
				hsw3000c01v3SelOut2TrapEnable
				AlarmEnable,
				hsw3000c01v3EqualUmid
				UmidStatus,
				hsw3000c01v3EqualUmidTrapEnable
				AlarmEnable,
				hsw3000c01v3Gpi3Stat
				BitFail,
				hsw3000c01v3Gpi3StatTrapEnable
				AlarmEnable,
				hsw3000c01v3In1PhyFail
				BitFail,
				hsw3000c01v3In1PhyFailTrapEnable
				AlarmEnable,
				hsw3000c01v3In1FmtFail
				BitFail,
				hsw3000c01v3In1FmtFailTrapEnable
				AlarmEnable,
				hsw3000c01v3In1IncFail
				BitFail,
				hsw3000c01v3In1IncFailTrapEnable
				AlarmEnable,
				hsw3000c01v3In1GpiFail
				BitFail,
				hsw3000c01v3In1GpiFailTrapEnable
				AlarmEnable,
				hsw3000c01v3In1BlkFail
				BitFail,
				hsw3000c01v3In1BlkFailTrapEnable
				AlarmEnable,
				hsw3000c01v3In1FrzFail
				BitFail,
				hsw3000c01v3In1FrzFailTrapEnable
				AlarmEnable,
				hsw3000c01v3In1PatFail
				BitFail,
				hsw3000c01v3In1PatFailTrapEnable
				AlarmEnable,
				hsw3000c01v3In1CrcFail
				BitFail,
				hsw3000c01v3In1CrcFailTrapEnable
				AlarmEnable,
				hsw3000c01v3In1SilFail
				BitFail,
				hsw3000c01v3In1SilFailTrapEnable
				AlarmEnable,
				hsw3000c01v3In1OvrFail
				BitFail,
				hsw3000c01v3In1OvrFailTrapEnable
				AlarmEnable,
				hsw3000c01v3In1PhFail
				BitFail,
				hsw3000c01v3In1PhFailTrapEnable
				AlarmEnable,
				hsw3000c01v3In1PreFail
				BitFail,
				hsw3000c01v3In1PreFailTrapEnable
				AlarmEnable,
				hsw3000c01v3In2PhyFail
				BitFail,
				hsw3000c01v3In2PhyFailTrapEnable
				AlarmEnable,
				hsw3000c01v3In2FmtFail
				BitFail,
				hsw3000c01v3In2FmtFailTrapEnable
				AlarmEnable,
				hsw3000c01v3In2IncFail
				BitFail,
				hsw3000c01v3In2IncFailTrapEnable
				AlarmEnable,
				hsw3000c01v3In2GpiFail
				BitFail,
				hsw3000c01v3In2GpiFailTrapEnable
				AlarmEnable,
				hsw3000c01v3In2BlkFail
				BitFail,
				hsw3000c01v3In2BlkFailTrapEnable
				AlarmEnable,
				hsw3000c01v3In2FrzFail
				BitFail,
				hsw3000c01v3In2FrzFailTrapEnable
				AlarmEnable,
				hsw3000c01v3In2PatFail
				BitFail,
				hsw3000c01v3In2PatFailTrapEnable
				AlarmEnable,
				hsw3000c01v3In2CrcFail
				BitFail,
				hsw3000c01v3In2CrcFailTrapEnable
				AlarmEnable,
				hsw3000c01v3In2SilFail
				BitFail,
				hsw3000c01v3In2SilFailTrapEnable
				AlarmEnable,
				hsw3000c01v3In2OvrFail
				BitFail,
				hsw3000c01v3In2OvrFailTrapEnable
				AlarmEnable,
				hsw3000c01v3In2PhFail
				BitFail,
				hsw3000c01v3In2PhFailTrapEnable
				AlarmEnable,
				hsw3000c01v3In2PreFail
				BitFail,
				hsw3000c01v3In2PreFailTrapEnable
				AlarmEnable,
				hsw3000c01v3RefFail
				BitFail,
				hsw3000c01v3RefFailTrapEnable
				AlarmEnable,
				hsw3000c01v3LockFail
				BitFail,
				hsw3000c01v3LockFailTrapEnable
				AlarmEnable,
				hsw3000c01v3BliGpiFail
				BitFail,
				hsw3000c01v3In1Format
				SdiHd3gFmt3,
				hsw3000c01v3In1FormatTrapEnable
				AlarmEnable,
				hsw3000c01v3In2Format
				SdiHd3gFmt3,
				hsw3000c01v3In2FormatTrapEnable
				AlarmEnable,
				hsw3000c01v3RefFormat
				SdiHd3gFmt3,
				hsw3000c01v3RefFormatTrapEnable
				AlarmEnable,
				hsw3000c01v3In1PidPres
				Bit0No1Yes,
				hsw3000c01v3In2PidPres
				Bit0No1Yes,
				hsw3000c01v3In1UmidPres
				Bit0No1Yes,
				hsw3000c01v3In2UmidPres
				Bit0No1Yes,
				hsw3000c01v3In1Grp1Pres
				Bit0No1Yes,
				hsw3000c01v3In1Grp1PresTrapEnable
				AlarmEnable,
				hsw3000c01v3In1Grp2Pres
				Bit0No1Yes,
				hsw3000c01v3In1Grp2PresTrapEnable
				AlarmEnable,
				hsw3000c01v3In1Grp3Pres
				Bit0No1Yes,
				hsw3000c01v3In1Grp3PresTrapEnable
				AlarmEnable,
				hsw3000c01v3In1Grp4Pres
				Bit0No1Yes,
				hsw3000c01v3In1Grp4PresTrapEnable
				AlarmEnable,
				hsw3000c01v3In1Grp1P0Stat
				AudioStatus,
				hsw3000c01v3In1Grp1P0StatTrapEnable
				AlarmEnable,
				hsw3000c01v3In1Grp1P1Stat
				AudioStatus,
				hsw3000c01v3In1Grp1P1StatTrapEnable
				AlarmEnable,
				hsw3000c01v3In1Grp2P0Stat
				AudioStatus,
				hsw3000c01v3In1Grp2P0StatTrapEnable
				AlarmEnable,
				hsw3000c01v3In1Grp2P1Stat
				AudioStatus,
				hsw3000c01v3In1Grp2P1StatTrapEnable
				AlarmEnable,
				hsw3000c01v3In1Grp3P0Stat
				AudioStatus,
				hsw3000c01v3In1Grp3P0StatTrapEnable
				AlarmEnable,
				hsw3000c01v3In1Grp3P1Stat
				AudioStatus,
				hsw3000c01v3In1Grp3P1StatTrapEnable
				AlarmEnable,
				hsw3000c01v3In1Grp4P0Stat
				AudioStatus,
				hsw3000c01v3In1Grp4P0StatTrapEnable
				AlarmEnable,
				hsw3000c01v3In1Grp4P1Stat
				AudioStatus,
				hsw3000c01v3In1Grp4P1StatTrapEnable
				AlarmEnable,
				hsw3000c01v3In2Grp1Pres
				Bit0No1Yes,
				hsw3000c01v3In2Grp1PresTrapEnable
				AlarmEnable,
				hsw3000c01v3In2Grp2Pres
				Bit0No1Yes,
				hsw3000c01v3In2Grp2PresTrapEnable
				AlarmEnable,
				hsw3000c01v3In2Grp3Pres
				Bit0No1Yes,
				hsw3000c01v3In2Grp3PresTrapEnable
				AlarmEnable,
				hsw3000c01v3In2Grp4Pres
				Bit0No1Yes,
				hsw3000c01v3In2Grp4PresTrapEnable
				AlarmEnable,
				hsw3000c01v3In2Grp1P0Stat
				AudioStatus,
				hsw3000c01v3In2Grp1P0StatTrapEnable
				AlarmEnable,
				hsw3000c01v3In2Grp1P1Stat
				AudioStatus,
				hsw3000c01v3In2Grp1P1StatTrapEnable
				AlarmEnable,
				hsw3000c01v3In2Grp2P0Stat
				AudioStatus,
				hsw3000c01v3In2Grp2P0StatTrapEnable
				AlarmEnable,
				hsw3000c01v3In2Grp2P1Stat
				AudioStatus,
				hsw3000c01v3In2Grp2P1StatTrapEnable
				AlarmEnable,
				hsw3000c01v3In2Grp3P0Stat
				AudioStatus,
				hsw3000c01v3In2Grp3P0StatTrapEnable
				AlarmEnable,
				hsw3000c01v3In2Grp3P1Stat
				AudioStatus,
				hsw3000c01v3In2Grp3P1StatTrapEnable
				AlarmEnable,
				hsw3000c01v3In2Grp4P0Stat
				AudioStatus,
				hsw3000c01v3In2Grp4P0StatTrapEnable
				AlarmEnable,
				hsw3000c01v3In2Grp4P1Stat
				AudioStatus,
				hsw3000c01v3In2Grp4P1StatTrapEnable
				AlarmEnable,
				hsw3000c01v3In1WssStat
				AfdInfo,
				hsw3000c01v3In1WssStatTrapEnable
				AlarmEnable,
				hsw3000c01v3In1ViiStat
				AfdInfo,
				hsw3000c01v3In1ViiStatTrapEnable
				AlarmEnable,
				hsw3000c01v3In12016Stat
				AfdInfo,
				hsw3000c01v3In12016StatTrapEnable
				AlarmEnable,
				hsw3000c01v3In2WssStat
				AfdInfo,
				hsw3000c01v3In2WssStatTrapEnable
				AlarmEnable,
				hsw3000c01v3In2ViiStat
				AfdInfo,
				hsw3000c01v3In2ViiStatTrapEnable
				AlarmEnable,
				hsw3000c01v3In22016Stat
				AfdInfo,
				hsw3000c01v3In22016StatTrapEnable
				AlarmEnable,
				hsw3000c01v3In1TxtLinLow
				Bit0No1Yes,
				hsw3000c01v3In1TxtLinLowTrapEnable
				AlarmEnable,
				hsw3000c01v3In1TxtLin1s
				Uint11,
				hsw3000c01v3In2TxtLinLow
				Bit0No1Yes,
				hsw3000c01v3In2TxtLinLowTrapEnable
				AlarmEnable,
				hsw3000c01v3In2TxtLin1s
				Uint11,
				hsw3000c01v3SerialNo
				SerialNo,
				hsw3000c01v3GpoMode
				Bit0No1Yes,
				hsw3000c01v3DePer2IncIn1
				Bit0Dis1Ena,
				hsw3000c01v3DePer2IncIn2
				Bit0Dis1Ena,
				hsw3000c01v3FrzToBckTime
				TimeS2,
				hsw3000c01v3In1WssCod
				Code4Bit,
				hsw3000c01v3In1WssCodTrapEnable
				AlarmEnable,
				hsw3000c01v3In1ViiAfdCod
				Code4Bit,
				hsw3000c01v3In1ViiAfdCodTrapEnable
				AlarmEnable,
				hsw3000c01v3In12016AfdCod
				Code4Bit,
				hsw3000c01v3In12016AfdCodTrapEnable
				AlarmEnable,
				hsw3000c01v3In2WssCod
				Code4Bit,
				hsw3000c01v3In2WssCodTrapEnable
				AlarmEnable,
				hsw3000c01v3In2ViiAfdCod
				Code4Bit,
				hsw3000c01v3In2ViiAfdCodTrapEnable
				AlarmEnable,
				hsw3000c01v3In22016Cod
				Code4Bit,
				hsw3000c01v3In22016CodTrapEnable
				AlarmEnable
			 }

		-- 1.3.6.1.4.1.10106.3.101291.1.1.1
		hsw3000c01v3Index OBJECT-TYPE
			SYNTAX ModuleIndex
			MAX-ACCESS read-only
			STATUS current
			DESCRIPTION
				"Index of HSW3000C01V3 Table"
		::= { hsw3000c01v3Entry 1 }

		-- 1.3.6.1.4.1.10106.3.101291.1.1.3
		hsw3000c01v3ActivePreset OBJECT-TYPE
			SYNTAX PresetActive
			MAX-ACCESS read-only
			STATUS current
			DESCRIPTION
				"Shows the active preset"
		::= { hsw3000c01v3Entry 3 }

		-- 1.3.6.1.4.1.10106.3.101291.1.1.5
		hsw3000c01v3LoadPreset OBJECT-TYPE
			SYNTAX PresetLoad
			MAX-ACCESS read-write
			STATUS current
			DESCRIPTION
				"Allows loading a preset"
		::= { hsw3000c01v3Entry 5 }

		-- 1.3.6.1.4.1.10106.3.101291.1.1.7
		hsw3000c01v3SavePreset OBJECT-TYPE
			SYNTAX PresetSave
			MAX-ACCESS read-write
			STATUS current
			DESCRIPTION
				"Allows saving a preset"
		::= { hsw3000c01v3Entry 7 }

		-- 1.3.6.1.4.1.10106.3.101291.1.1.9
		hsw3000c01v3StateSel OBJECT-TYPE
			SYNTAX HswState
			MAX-ACCESS read-write
			STATUS current
			DESCRIPTION
				"Shows the module's current state"
		::= { hsw3000c01v3Entry 9 }

		-- 1.3.6.1.4.1.10106.3.101291.1.1.10
		hsw3000c01v3StateSelTrapEnable OBJECT-TYPE
			SYNTAX AlarmEnable
			MAX-ACCESS read-write
			STATUS current
			DESCRIPTION
				"Shows the module's current state Trap Enable"
		::= { hsw3000c01v3Entry 10 }

		-- 1.3.6.1.4.1.10106.3.101291.1.1.11
		hsw3000c01v3SwitchMode OBJECT-TYPE
			SYNTAX HswSwMode
			MAX-ACCESS read-write
			STATUS current
			DESCRIPTION
				"Allows selecting the switching mode"
		::= { hsw3000c01v3Entry 11 }

		-- 1.3.6.1.4.1.10106.3.101291.1.1.12
		hsw3000c01v3SwitchModeTrapEnable OBJECT-TYPE
			SYNTAX AlarmEnable
			MAX-ACCESS read-write
			STATUS current
			DESCRIPTION
				"Allows selecting the switching mode Trap Enable"
		::= { hsw3000c01v3Entry 12 }

		-- 1.3.6.1.4.1.10106.3.101291.1.1.13
		hsw3000c01v3FreezeMode OBJECT-TYPE
			SYNTAX HswFreezeMode
			MAX-ACCESS read-write
			STATUS current
			DESCRIPTION
				"Allows selecting the freeze detection mode"
		::= { hsw3000c01v3Entry 13 }

		-- 1.3.6.1.4.1.10106.3.101291.1.1.15
		hsw3000c01v3BypassEnable OBJECT-TYPE
			SYNTAX Bit0Dis1Ena
			MAX-ACCESS read-write
			STATUS current
			DESCRIPTION
				"Allows activating the rear board bypass"
		::= { hsw3000c01v3Entry 15 }

		-- 1.3.6.1.4.1.10106.3.101291.1.1.16
		hsw3000c01v3BypassEnableTrapEnable OBJECT-TYPE
			SYNTAX AlarmEnable
			MAX-ACCESS read-write
			STATUS current
			DESCRIPTION
				"Allows activating the rear board bypass Trap Enable"
		::= { hsw3000c01v3Entry 16 }

		-- 1.3.6.1.4.1.10106.3.101291.1.1.17
		hsw3000c01v3InpFailMode OBJECT-TYPE
			SYNTAX Bit0No1Yes
			MAX-ACCESS read-write
			STATUS current
			DESCRIPTION
				"Selects if the output is muted when the selected input fails"
		::= { hsw3000c01v3Entry 17 }

		-- 1.3.6.1.4.1.10106.3.101291.1.1.19
		hsw3000c01v3OperatingMode OBJECT-TYPE
			SYNTAX HswOperMode
			MAX-ACCESS read-write
			STATUS current
			DESCRIPTION
				"Allows selecting the operating mode"
		::= { hsw3000c01v3Entry 19 }

		-- 1.3.6.1.4.1.10106.3.101291.1.1.20
		hsw3000c01v3OperatingModeTrapEnable OBJECT-TYPE
			SYNTAX AlarmEnable
			MAX-ACCESS read-write
			STATUS current
			DESCRIPTION
				"Allows selecting the operating mode Trap Enable"
		::= { hsw3000c01v3Entry 20 }

		-- 1.3.6.1.4.1.10106.3.101291.1.1.21
		hsw3000c01v3StateAMap OBJECT-TYPE
			SYNTAX HswMapState
			MAX-ACCESS read-write
			STATUS current
			DESCRIPTION
				"Allow selecting the input to output mapping when state A is selected"
		::= { hsw3000c01v3Entry 21 }

		-- 1.3.6.1.4.1.10106.3.101291.1.1.23
		hsw3000c01v3StateBMap OBJECT-TYPE
			SYNTAX HswMapState
			MAX-ACCESS read-write
			STATUS current
			DESCRIPTION
				"Allow selecting the input to output mapping when state B is selected"
		::= { hsw3000c01v3Entry 23 }

		-- 1.3.6.1.4.1.10106.3.101291.1.1.25
		hsw3000c01v3StateAGpo OBJECT-TYPE
			SYNTAX HswGpoState
			MAX-ACCESS read-write
			STATUS current
			DESCRIPTION
				"Allow selecting the GPO configuration when state A is selected"
		::= { hsw3000c01v3Entry 25 }

		-- 1.3.6.1.4.1.10106.3.101291.1.1.27
		hsw3000c01v3StateBGpo OBJECT-TYPE
			SYNTAX HswGpoState
			MAX-ACCESS read-write
			STATUS current
			DESCRIPTION
				"Allow selecting the GPO configuration when state B is selected"
		::= { hsw3000c01v3Entry 27 }

		-- 1.3.6.1.4.1.10106.3.101291.1.1.29
		hsw3000c01v3AnaRefFmt OBJECT-TYPE
			SYNTAX SdiHd3gFmt5
			MAX-ACCESS read-write
			STATUS current
			DESCRIPTION
				"Analog reference input format"
		::= { hsw3000c01v3Entry 29 }

		-- 1.3.6.1.4.1.10106.3.101291.1.1.31
		hsw3000c01v3In1StChange OBJECT-TYPE
			SYNTAX Bit0No1Yes
			MAX-ACCESS read-write
			STATUS current
			DESCRIPTION
				"Signals a change in fail status"
		::= { hsw3000c01v3Entry 31 }

		-- 1.3.6.1.4.1.10106.3.101291.1.1.33
		hsw3000c01v3In2StChange OBJECT-TYPE
			SYNTAX Bit0No1Yes
			MAX-ACCESS read-write
			STATUS current
			DESCRIPTION
				"Signals a change in fail status"
		::= { hsw3000c01v3Entry 33 }

		-- 1.3.6.1.4.1.10106.3.101291.1.1.35
		hsw3000c01v3Gpi1StChange OBJECT-TYPE
			SYNTAX Bit0No1Yes
			MAX-ACCESS read-write
			STATUS current
			DESCRIPTION
				"Signals a change in GPI fail status"
		::= { hsw3000c01v3Entry 35 }

		-- 1.3.6.1.4.1.10106.3.101291.1.1.37
		hsw3000c01v3Gpi2StChange OBJECT-TYPE
			SYNTAX Bit0No1Yes
			MAX-ACCESS read-write
			STATUS current
			DESCRIPTION
				"Signals a change in GPI fail status"
		::= { hsw3000c01v3Entry 37 }

		-- 1.3.6.1.4.1.10106.3.101291.1.1.39
		hsw3000c01v3Gpi3StChange OBJECT-TYPE
			SYNTAX Bit0No1Yes
			MAX-ACCESS read-write
			STATUS current
			DESCRIPTION
				"Signals a change in GPI fail status (GPI2B)"
		::= { hsw3000c01v3Entry 39 }

		-- 1.3.6.1.4.1.10106.3.101291.1.1.41
		hsw3000c01v3InputChange OBJECT-TYPE
			SYNTAX Bit0No1Yes
			MAX-ACCESS read-write
			STATUS current
			DESCRIPTION
				"Signals a change in selected input"
		::= { hsw3000c01v3Entry 41 }

		-- 1.3.6.1.4.1.10106.3.101291.1.1.43
		hsw3000c01v3VDelay OBJECT-TYPE
			SYNTAX DelayLines2
			MAX-ACCESS read-write
			STATUS current
			DESCRIPTION
				"Allows adjusting the video vertical delay"
		::= { hsw3000c01v3Entry 43 }

		-- 1.3.6.1.4.1.10106.3.101291.1.1.45
		hsw3000c01v3HDelay OBJECT-TYPE
			SYNTAX DelayPixel5
			MAX-ACCESS read-write
			STATUS current
			DESCRIPTION
				"Allows adjusting the video horizontal delay"
		::= { hsw3000c01v3Entry 45 }

		-- 1.3.6.1.4.1.10106.3.101291.1.1.47
		hsw3000c01v3Holdoff OBJECT-TYPE
			SYNTAX TimeS2
			MAX-ACCESS read-write
			STATUS current
			DESCRIPTION
				"Elapsed time after a switch event before a new switch occurs"
		::= { hsw3000c01v3Entry 47 }

		-- 1.3.6.1.4.1.10106.3.101291.1.1.49
		hsw3000c01v3PhyFailTim OBJECT-TYPE
			SYNTAX HswTiming
			MAX-ACCESS read-write
			STATUS current
			DESCRIPTION
				"Allows selecting the desired timing for the physical fail"
		::= { hsw3000c01v3Entry 49 }

		-- 1.3.6.1.4.1.10106.3.101291.1.1.51
		hsw3000c01v3FmtFailTim OBJECT-TYPE
			SYNTAX HswTiming
			MAX-ACCESS read-write
			STATUS current
			DESCRIPTION
				"Allows selecting the desired timing for the format fail"
		::= { hsw3000c01v3Entry 51 }

		-- 1.3.6.1.4.1.10106.3.101291.1.1.53
		hsw3000c01v3IncFailTim OBJECT-TYPE
			SYNTAX HswTiming
			MAX-ACCESS read-write
			STATUS current
			DESCRIPTION
				"Allows selecting the desired timing for the incompatible format fail"
		::= { hsw3000c01v3Entry 53 }

		-- 1.3.6.1.4.1.10106.3.101291.1.1.55
		hsw3000c01v3StatusMode OBJECT-TYPE
			SYNTAX StatusMode
			MAX-ACCESS read-write
			STATUS current
			DESCRIPTION
				"Allows selecting if status informaction is afected by activation/desactivation timing"
		::= { hsw3000c01v3Entry 55 }

		-- 1.3.6.1.4.1.10106.3.101291.1.1.57
		hsw3000c01v3SynchroModeIn1 OBJECT-TYPE
			SYNTAX Bit0Fra1Lin
			MAX-ACCESS read-write
			STATUS current
			DESCRIPTION
				"Allows selecting the synchronizing mode"
		::= { hsw3000c01v3Entry 57 }

		-- 1.3.6.1.4.1.10106.3.101291.1.1.59
		hsw3000c01v3SynchroModeIn2 OBJECT-TYPE
			SYNTAX Bit0Fra1Lin
			MAX-ACCESS read-write
			STATUS current
			DESCRIPTION
				"Allows selecting the synchronizing mode"
		::= { hsw3000c01v3Entry 59 }

		-- 1.3.6.1.4.1.10106.3.101291.1.1.61
		hsw3000c01v3GpiFailTim OBJECT-TYPE
			SYNTAX HswTiming
			MAX-ACCESS read-write
			STATUS current
			DESCRIPTION
				"Allows selecting the desired timing for the GPI fail"
		::= { hsw3000c01v3Entry 61 }

		-- 1.3.6.1.4.1.10106.3.101291.1.1.63
		hsw3000c01v3BlkFailTim OBJECT-TYPE
			SYNTAX HswTiming
			MAX-ACCESS read-write
			STATUS current
			DESCRIPTION
				"Allows selecting the desired timing for the black fail"
		::= { hsw3000c01v3Entry 63 }

		-- 1.3.6.1.4.1.10106.3.101291.1.1.65
		hsw3000c01v3FrzFailTim OBJECT-TYPE
			SYNTAX HswTiming
			MAX-ACCESS read-write
			STATUS current
			DESCRIPTION
				"Allows selecting the desired timing for the freeze fail"
		::= { hsw3000c01v3Entry 65 }

		-- 1.3.6.1.4.1.10106.3.101291.1.1.67
		hsw3000c01v3PatFailTim OBJECT-TYPE
			SYNTAX HswTiming
			MAX-ACCESS read-write
			STATUS current
			DESCRIPTION
				"Allows selecting the desired timing for the pattern fail"
		::= { hsw3000c01v3Entry 67 }

		-- 1.3.6.1.4.1.10106.3.101291.1.1.69
		hsw3000c01v3CrcFailTim OBJECT-TYPE
			SYNTAX HswTiming
			MAX-ACCESS read-write
			STATUS current
			DESCRIPTION
				"Allows selecting the desired timing for the EDH/CRC"
		::= { hsw3000c01v3Entry 69 }

		-- 1.3.6.1.4.1.10106.3.101291.1.1.71
		hsw3000c01v3SilFailTim OBJECT-TYPE
			SYNTAX HswTiming
			MAX-ACCESS read-write
			STATUS current
			DESCRIPTION
				"Allows selecting the desired timing for the audio silence fail"
		::= { hsw3000c01v3Entry 71 }

		-- 1.3.6.1.4.1.10106.3.101291.1.1.73
		hsw3000c01v3OvrFailTim OBJECT-TYPE
			SYNTAX HswTiming
			MAX-ACCESS read-write
			STATUS current
			DESCRIPTION
				"Allows selecting the desired timing for the audio overload fail"
		::= { hsw3000c01v3Entry 73 }

		-- 1.3.6.1.4.1.10106.3.101291.1.1.75
		hsw3000c01v3PhFailTim OBJECT-TYPE
			SYNTAX HswTiming
			MAX-ACCESS read-write
			STATUS current
			DESCRIPTION
				"Allows selecting the desired timing for the audio phase fail"
		::= { hsw3000c01v3Entry 75 }

		-- 1.3.6.1.4.1.10106.3.101291.1.1.77
		hsw3000c01v3PresFailTim OBJECT-TYPE
			SYNTAX HswTiming
			MAX-ACCESS read-write
			STATUS current
			DESCRIPTION
				"Allows selecting the desired timing for the audio presence fail"
		::= { hsw3000c01v3Entry 77 }

		-- 1.3.6.1.4.1.10106.3.101291.1.1.79
		hsw3000c01v3ActPer1 OBJECT-TYPE
			SYNTAX TimeS2
			MAX-ACCESS read-write
			STATUS current
			DESCRIPTION
				"Activation time used in timing 1"
		::= { hsw3000c01v3Entry 79 }

		-- 1.3.6.1.4.1.10106.3.101291.1.1.81
		hsw3000c01v3DeactPer1 OBJECT-TYPE
			SYNTAX TimeS2
			MAX-ACCESS read-write
			STATUS current
			DESCRIPTION
				"Deactivation time used in timing 1"
		::= { hsw3000c01v3Entry 81 }

		-- 1.3.6.1.4.1.10106.3.101291.1.1.83
		hsw3000c01v3ActPer2 OBJECT-TYPE
			SYNTAX TimeS2
			MAX-ACCESS read-write
			STATUS current
			DESCRIPTION
				"Activation time used in timing 2"
		::= { hsw3000c01v3Entry 83 }

		-- 1.3.6.1.4.1.10106.3.101291.1.1.85
		hsw3000c01v3DeactPer2 OBJECT-TYPE
			SYNTAX TimeS2
			MAX-ACCESS read-write
			STATUS current
			DESCRIPTION
				"Deactivation time used in timing 2"
		::= { hsw3000c01v3Entry 85 }

		-- 1.3.6.1.4.1.10106.3.101291.1.1.87
		hsw3000c01v3CrcThreshold OBJECT-TYPE
			SYNTAX Rate2
			MAX-ACCESS read-write
			STATUS current
			DESCRIPTION
				"Allows adjusting the threshold that activates the EDH/CRC fail"
		::= { hsw3000c01v3Entry 87 }

		-- 1.3.6.1.4.1.10106.3.101291.1.1.89
		hsw3000c01v3BlackThreshold OBJECT-TYPE
			SYNTAX BlackThreshold
			MAX-ACCESS read-write
			STATUS current
			DESCRIPTION
				"Allows adjusting the threshold thas activates the black fail"
		::= { hsw3000c01v3Entry 89 }

		-- 1.3.6.1.4.1.10106.3.101291.1.1.91
		hsw3000c01v3VertFrozenWin OBJECT-TYPE
			SYNTAX Rate1
			MAX-ACCESS read-write
			STATUS current
			DESCRIPTION
				"Allows adjusting the vertical size of the window used in the freeze detector"
		::= { hsw3000c01v3Entry 91 }

		-- 1.3.6.1.4.1.10106.3.101291.1.1.93
		hsw3000c01v3HtalFrozenWin OBJECT-TYPE
			SYNTAX Rate1
			MAX-ACCESS read-write
			STATUS current
			DESCRIPTION
				"Allows adjusting the horizontal size of the window used in the freeze detector"
		::= { hsw3000c01v3Entry 93 }

		-- 1.3.6.1.4.1.10106.3.101291.1.1.95
		hsw3000c01v3In1PhyFailMsk OBJECT-TYPE
			SYNTAX BitMask
			MAX-ACCESS read-write
			STATUS current
			DESCRIPTION
				"Allows masking the signal absence fail"
		::= { hsw3000c01v3Entry 95 }

		-- 1.3.6.1.4.1.10106.3.101291.1.1.97
		hsw3000c01v3In1FmtFailMsk OBJECT-TYPE
			SYNTAX BitMask
			MAX-ACCESS read-write
			STATUS current
			DESCRIPTION
				"Allows masking the format fail"
		::= { hsw3000c01v3Entry 97 }

		-- 1.3.6.1.4.1.10106.3.101291.1.1.99
		hsw3000c01v3In1IncFailMsk OBJECT-TYPE
			SYNTAX BitMask
			MAX-ACCESS read-write
			STATUS current
			DESCRIPTION
				"Allows masking the incompatible format fail"
		::= { hsw3000c01v3Entry 99 }

		-- 1.3.6.1.4.1.10106.3.101291.1.1.101
		hsw3000c01v3In1GpiFailMsk OBJECT-TYPE
			SYNTAX BitMask
			MAX-ACCESS read-write
			STATUS current
			DESCRIPTION
				"Allows masking the GPI fail"
		::= { hsw3000c01v3Entry 101 }

		-- 1.3.6.1.4.1.10106.3.101291.1.1.103
		hsw3000c01v3In1BlkFailMsk OBJECT-TYPE
			SYNTAX BitMask
			MAX-ACCESS read-write
			STATUS current
			DESCRIPTION
				"Allows masking the black signal fail"
		::= { hsw3000c01v3Entry 103 }

		-- 1.3.6.1.4.1.10106.3.101291.1.1.105
		hsw3000c01v3In1FrzFailMsk OBJECT-TYPE
			SYNTAX BitMask
			MAX-ACCESS read-write
			STATUS current
			DESCRIPTION
				"Allows masking the freeze signal fail"
		::= { hsw3000c01v3Entry 105 }

		-- 1.3.6.1.4.1.10106.3.101291.1.1.107
		hsw3000c01v3In1PatFailMsk OBJECT-TYPE
			SYNTAX BitMask
			MAX-ACCESS read-write
			STATUS current
			DESCRIPTION
				"Allows masking the video pattern fail"
		::= { hsw3000c01v3Entry 107 }

		-- 1.3.6.1.4.1.10106.3.101291.1.1.109
		hsw3000c01v3In1CrcFailMsk OBJECT-TYPE
			SYNTAX BitMask
			MAX-ACCESS read-write
			STATUS current
			DESCRIPTION
				"Allows masking the EDH/CRC"
		::= { hsw3000c01v3Entry 109 }

		-- 1.3.6.1.4.1.10106.3.101291.1.1.111
		hsw3000c01v3In1SilFailMsk OBJECT-TYPE
			SYNTAX BitMask
			MAX-ACCESS read-write
			STATUS current
			DESCRIPTION
				"Allows masking the audio silence fail"
		::= { hsw3000c01v3Entry 111 }

		-- 1.3.6.1.4.1.10106.3.101291.1.1.113
		hsw3000c01v3In1OvrFailMsk OBJECT-TYPE
			SYNTAX BitMask
			MAX-ACCESS read-write
			STATUS current
			DESCRIPTION
				"Allows masking the audio overload fail"
		::= { hsw3000c01v3Entry 113 }

		-- 1.3.6.1.4.1.10106.3.101291.1.1.115
		hsw3000c01v3In1PhFailMsk OBJECT-TYPE
			SYNTAX BitMask
			MAX-ACCESS read-write
			STATUS current
			DESCRIPTION
				"Allows masking the audio phase fail"
		::= { hsw3000c01v3Entry 115 }

		-- 1.3.6.1.4.1.10106.3.101291.1.1.117
		hsw3000c01v3In1PreFailMsk OBJECT-TYPE
			SYNTAX BitMask
			MAX-ACCESS read-write
			STATUS current
			DESCRIPTION
				"Allows masking the audio presence fail"
		::= { hsw3000c01v3Entry 117 }

		-- 1.3.6.1.4.1.10106.3.101291.1.1.119
		hsw3000c01v3In2PhyFailMsk OBJECT-TYPE
			SYNTAX BitMask
			MAX-ACCESS read-write
			STATUS current
			DESCRIPTION
				"Allows masking the signal absence fail"
		::= { hsw3000c01v3Entry 119 }

		-- 1.3.6.1.4.1.10106.3.101291.1.1.121
		hsw3000c01v3In2FmtFailMsk OBJECT-TYPE
			SYNTAX BitMask
			MAX-ACCESS read-write
			STATUS current
			DESCRIPTION
				"Allows masking the format fail"
		::= { hsw3000c01v3Entry 121 }

		-- 1.3.6.1.4.1.10106.3.101291.1.1.123
		hsw3000c01v3In2IncFailMsk OBJECT-TYPE
			SYNTAX BitMask
			MAX-ACCESS read-write
			STATUS current
			DESCRIPTION
				"Allows masking the incompatible format fail"
		::= { hsw3000c01v3Entry 123 }

		-- 1.3.6.1.4.1.10106.3.101291.1.1.125
		hsw3000c01v3In2GpiFailMsk OBJECT-TYPE
			SYNTAX BitMask
			MAX-ACCESS read-write
			STATUS current
			DESCRIPTION
				"Allows masking the GPI fail"
		::= { hsw3000c01v3Entry 125 }

		-- 1.3.6.1.4.1.10106.3.101291.1.1.127
		hsw3000c01v3In2BlkFailMsk OBJECT-TYPE
			SYNTAX BitMask
			MAX-ACCESS read-write
			STATUS current
			DESCRIPTION
				"Allows masking the black signal fail"
		::= { hsw3000c01v3Entry 127 }

		-- 1.3.6.1.4.1.10106.3.101291.1.1.129
		hsw3000c01v3In2FrzFailMsk OBJECT-TYPE
			SYNTAX BitMask
			MAX-ACCESS read-write
			STATUS current
			DESCRIPTION
				"Allows masking the freeze signal fail"
		::= { hsw3000c01v3Entry 129 }

		-- 1.3.6.1.4.1.10106.3.101291.1.1.131
		hsw3000c01v3In2PatFailMsk OBJECT-TYPE
			SYNTAX BitMask
			MAX-ACCESS read-write
			STATUS current
			DESCRIPTION
				"Allows masking the video pattern fail"
		::= { hsw3000c01v3Entry 131 }

		-- 1.3.6.1.4.1.10106.3.101291.1.1.133
		hsw3000c01v3In2CrcFailMsk OBJECT-TYPE
			SYNTAX BitMask
			MAX-ACCESS read-write
			STATUS current
			DESCRIPTION
				"Allows masking the EDH/CRC"
		::= { hsw3000c01v3Entry 133 }

		-- 1.3.6.1.4.1.10106.3.101291.1.1.135
		hsw3000c01v3In2SilFailMsk OBJECT-TYPE
			SYNTAX BitMask
			MAX-ACCESS read-write
			STATUS current
			DESCRIPTION
				"Allows masking the audio silence fail"
		::= { hsw3000c01v3Entry 135 }

		-- 1.3.6.1.4.1.10106.3.101291.1.1.137
		hsw3000c01v3In2OvrFailMsk OBJECT-TYPE
			SYNTAX BitMask
			MAX-ACCESS read-write
			STATUS current
			DESCRIPTION
				"Allows masking the audio overload fail"
		::= { hsw3000c01v3Entry 137 }

		-- 1.3.6.1.4.1.10106.3.101291.1.1.139
		hsw3000c01v3In2PhFailMsk OBJECT-TYPE
			SYNTAX BitMask
			MAX-ACCESS read-write
			STATUS current
			DESCRIPTION
				"Allows masking the audio phase fail"
		::= { hsw3000c01v3Entry 139 }

		-- 1.3.6.1.4.1.10106.3.101291.1.1.141
		hsw3000c01v3In2PreFailMsk OBJECT-TYPE
			SYNTAX BitMask
			MAX-ACCESS read-write
			STATUS current
			DESCRIPTION
				"Allows masking the audio presence fail"
		::= { hsw3000c01v3Entry 141 }

		-- 1.3.6.1.4.1.10106.3.101291.1.1.143
		hsw3000c01v3RefFailMsk OBJECT-TYPE
			SYNTAX BitMask
			MAX-ACCESS read-write
			STATUS current
			DESCRIPTION
				"Allows masking the reference absence fail"
		::= { hsw3000c01v3Entry 143 }

		-- 1.3.6.1.4.1.10106.3.101291.1.1.145
		hsw3000c01v3LockFailMsk OBJECT-TYPE
			SYNTAX BitMask
			MAX-ACCESS read-write
			STATUS current
			DESCRIPTION
				"Allows masking the reference unlock fail"
		::= { hsw3000c01v3Entry 145 }

		-- 1.3.6.1.4.1.10106.3.101291.1.1.147
		hsw3000c01v3In1AudG1p0Msk OBJECT-TYPE
			SYNTAX AudioMask
			MAX-ACCESS read-write
			STATUS current
			DESCRIPTION
				"Allows masking the audio in group 1 pair 0"
		::= { hsw3000c01v3Entry 147 }

		-- 1.3.6.1.4.1.10106.3.101291.1.1.149
		hsw3000c01v3In1AudG1p1Msk OBJECT-TYPE
			SYNTAX AudioMask
			MAX-ACCESS read-write
			STATUS current
			DESCRIPTION
				"Allows masking the audio in group 1 pair 1"
		::= { hsw3000c01v3Entry 149 }

		-- 1.3.6.1.4.1.10106.3.101291.1.1.151
		hsw3000c01v3In1AudG2p0Msk OBJECT-TYPE
			SYNTAX AudioMask
			MAX-ACCESS read-write
			STATUS current
			DESCRIPTION
				"Allows masking the audio in group 2 pair 0"
		::= { hsw3000c01v3Entry 151 }

		-- 1.3.6.1.4.1.10106.3.101291.1.1.153
		hsw3000c01v3In1AudG2p1Msk OBJECT-TYPE
			SYNTAX AudioMask
			MAX-ACCESS read-write
			STATUS current
			DESCRIPTION
				"Allows masking the audio in group 2 pair 1"
		::= { hsw3000c01v3Entry 153 }

		-- 1.3.6.1.4.1.10106.3.101291.1.1.155
		hsw3000c01v3In1AudG3p0Msk OBJECT-TYPE
			SYNTAX AudioMask
			MAX-ACCESS read-write
			STATUS current
			DESCRIPTION
				"Allows masking the audio in group 3 pair 0"
		::= { hsw3000c01v3Entry 155 }

		-- 1.3.6.1.4.1.10106.3.101291.1.1.157
		hsw3000c01v3In1AudG3p1Msk OBJECT-TYPE
			SYNTAX AudioMask
			MAX-ACCESS read-write
			STATUS current
			DESCRIPTION
				"Allows masking the audio in group 3 pair 1"
		::= { hsw3000c01v3Entry 157 }

		-- 1.3.6.1.4.1.10106.3.101291.1.1.159
		hsw3000c01v3In1AudG4p0Msk OBJECT-TYPE
			SYNTAX AudioMask
			MAX-ACCESS read-write
			STATUS current
			DESCRIPTION
				"Allows masking the audio in group 4 pair 0"
		::= { hsw3000c01v3Entry 159 }

		-- 1.3.6.1.4.1.10106.3.101291.1.1.161
		hsw3000c01v3In1AudG4p1Msk OBJECT-TYPE
			SYNTAX AudioMask
			MAX-ACCESS read-write
			STATUS current
			DESCRIPTION
				"Allows masking the audio in group 4 pair 1"
		::= { hsw3000c01v3Entry 161 }

		-- 1.3.6.1.4.1.10106.3.101291.1.1.163
		hsw3000c01v3In2AudG1p0Msk OBJECT-TYPE
			SYNTAX AudioMask
			MAX-ACCESS read-write
			STATUS current
			DESCRIPTION
				"Allows masking the audio in group 1 pair 0"
		::= { hsw3000c01v3Entry 163 }

		-- 1.3.6.1.4.1.10106.3.101291.1.1.165
		hsw3000c01v3In2AudG1p1Msk OBJECT-TYPE
			SYNTAX AudioMask
			MAX-ACCESS read-write
			STATUS current
			DESCRIPTION
				"Allows masking the audio in group 1 pair 1"
		::= { hsw3000c01v3Entry 165 }

		-- 1.3.6.1.4.1.10106.3.101291.1.1.167
		hsw3000c01v3In2AudG2p0Msk OBJECT-TYPE
			SYNTAX AudioMask
			MAX-ACCESS read-write
			STATUS current
			DESCRIPTION
				"Allows masking the audio in group 2 pair 0"
		::= { hsw3000c01v3Entry 167 }

		-- 1.3.6.1.4.1.10106.3.101291.1.1.169
		hsw3000c01v3In2AudG2p1Msk OBJECT-TYPE
			SYNTAX AudioMask
			MAX-ACCESS read-write
			STATUS current
			DESCRIPTION
				"Allows masking the audio in group 2 pair 1"
		::= { hsw3000c01v3Entry 169 }

		-- 1.3.6.1.4.1.10106.3.101291.1.1.171
		hsw3000c01v3In2AudG3p0Msk OBJECT-TYPE
			SYNTAX AudioMask
			MAX-ACCESS read-write
			STATUS current
			DESCRIPTION
				"Allows masking the audio in group 3 pair 0"
		::= { hsw3000c01v3Entry 171 }

		-- 1.3.6.1.4.1.10106.3.101291.1.1.173
		hsw3000c01v3In2AudG3p1Msk OBJECT-TYPE
			SYNTAX AudioMask
			MAX-ACCESS read-write
			STATUS current
			DESCRIPTION
				"Allows masking the audio in group 3 pair 1"
		::= { hsw3000c01v3Entry 173 }

		-- 1.3.6.1.4.1.10106.3.101291.1.1.175
		hsw3000c01v3In2AudG4p0Msk OBJECT-TYPE
			SYNTAX AudioMask
			MAX-ACCESS read-write
			STATUS current
			DESCRIPTION
				"Allows masking the audio in group 4 pair 0"
		::= { hsw3000c01v3Entry 175 }

		-- 1.3.6.1.4.1.10106.3.101291.1.1.177
		hsw3000c01v3In2AudG4p1Msk OBJECT-TYPE
			SYNTAX AudioMask
			MAX-ACCESS read-write
			STATUS current
			DESCRIPTION
				"Allows masking the audio in group 4 pair 1"
		::= { hsw3000c01v3Entry 177 }

		-- 1.3.6.1.4.1.10106.3.101291.1.1.179
		hsw3000c01v3SilenceLevel OBJECT-TYPE
			SYNTAX LevelDbfs3
			MAX-ACCESS read-write
			STATUS current
			DESCRIPTION
				"Allows adjusting the threshold level for the silence detector"
		::= { hsw3000c01v3Entry 179 }

		-- 1.3.6.1.4.1.10106.3.101291.1.1.181
		hsw3000c01v3SilenceTime OBJECT-TYPE
			SYNTAX TimeS2
			MAX-ACCESS read-write
			STATUS current
			DESCRIPTION
				"Allows adjusting the time for the silence detector"
		::= { hsw3000c01v3Entry 181 }

		-- 1.3.6.1.4.1.10106.3.101291.1.1.183
		hsw3000c01v3OverloadLevel OBJECT-TYPE
			SYNTAX LevelDbfs4
			MAX-ACCESS read-write
			STATUS current
			DESCRIPTION
				"Allows adjusting the threshold level for the overload detector"
		::= { hsw3000c01v3Entry 183 }

		-- 1.3.6.1.4.1.10106.3.101291.1.1.185
		hsw3000c01v3TxtLinesThrs OBJECT-TYPE
			SYNTAX TxtThreshold
			MAX-ACCESS read-write
			STATUS current
			DESCRIPTION
				"Low teletext line number threshold"
		::= { hsw3000c01v3Entry 185 }

		-- 1.3.6.1.4.1.10106.3.101291.1.1.187
		hsw3000c01v3In1Fail OBJECT-TYPE
			SYNTAX BitFail
			MAX-ACCESS read-only
			STATUS current
			DESCRIPTION
				"Input 1 fail"
		::= { hsw3000c01v3Entry 187 }

		-- 1.3.6.1.4.1.10106.3.101291.1.1.188
		hsw3000c01v3In1FailTrapEnable OBJECT-TYPE
			SYNTAX AlarmEnable
			MAX-ACCESS read-write
			STATUS current
			DESCRIPTION
				"Input 1 fail Trap Enable"
		::= { hsw3000c01v3Entry 188 }

		-- 1.3.6.1.4.1.10106.3.101291.1.1.189
		hsw3000c01v3In2Fail OBJECT-TYPE
			SYNTAX BitFail
			MAX-ACCESS read-only
			STATUS current
			DESCRIPTION
				"Input 2 fail"
		::= { hsw3000c01v3Entry 189 }

		-- 1.3.6.1.4.1.10106.3.101291.1.1.190
		hsw3000c01v3In2FailTrapEnable OBJECT-TYPE
			SYNTAX AlarmEnable
			MAX-ACCESS read-write
			STATUS current
			DESCRIPTION
				"Input 2 fail Trap Enable"
		::= { hsw3000c01v3Entry 190 }

		-- 1.3.6.1.4.1.10106.3.101291.1.1.191
		hsw3000c01v3In1ExtFail OBJECT-TYPE
			SYNTAX BitFail
			MAX-ACCESS read-only
			STATUS current
			DESCRIPTION
				"Input 1 GPI fail (GPI1A)"
		::= { hsw3000c01v3Entry 191 }

		-- 1.3.6.1.4.1.10106.3.101291.1.1.192
		hsw3000c01v3In1ExtFailTrapEnable OBJECT-TYPE
			SYNTAX AlarmEnable
			MAX-ACCESS read-write
			STATUS current
			DESCRIPTION
				"Input 1 GPI fail (GPI1A) Trap Enable"
		::= { hsw3000c01v3Entry 192 }

		-- 1.3.6.1.4.1.10106.3.101291.1.1.193
		hsw3000c01v3In2ExtFail OBJECT-TYPE
			SYNTAX BitFail
			MAX-ACCESS read-only
			STATUS current
			DESCRIPTION
				"Input 2 GPI fail (GPI2A)"
		::= { hsw3000c01v3Entry 193 }

		-- 1.3.6.1.4.1.10106.3.101291.1.1.194
		hsw3000c01v3In2ExtFailTrapEnable OBJECT-TYPE
			SYNTAX AlarmEnable
			MAX-ACCESS read-write
			STATUS current
			DESCRIPTION
				"Input 2 GPI fail (GPI2A) Trap Enable"
		::= { hsw3000c01v3Entry 194 }

		-- 1.3.6.1.4.1.10106.3.101291.1.1.195
		hsw3000c01v3BlindExtFail OBJECT-TYPE
			SYNTAX BitFail
			MAX-ACCESS read-only
			STATUS current
			DESCRIPTION
				"Blind halfauto control GPI fail (GPI2B)"
		::= { hsw3000c01v3Entry 195 }

		-- 1.3.6.1.4.1.10106.3.101291.1.1.196
		hsw3000c01v3BlindExtFailTrapEnable OBJECT-TYPE
			SYNTAX AlarmEnable
			MAX-ACCESS read-write
			STATUS current
			DESCRIPTION
				"Blind halfauto control GPI fail (GPI2B) Trap Enable"
		::= { hsw3000c01v3Entry 196 }

		-- 1.3.6.1.4.1.10106.3.101291.1.1.197
		hsw3000c01v3EqualPid OBJECT-TYPE
			SYNTAX UmidStatus
			MAX-ACCESS read-only
			STATUS current
			DESCRIPTION
				"Indicates if both  inputs have same PID"
		::= { hsw3000c01v3Entry 197 }

		-- 1.3.6.1.4.1.10106.3.101291.1.1.198
		hsw3000c01v3EqualPidTrapEnable OBJECT-TYPE
			SYNTAX AlarmEnable
			MAX-ACCESS read-write
			STATUS current
			DESCRIPTION
				"Indicates if both  inputs have same PID Trap Enable"
		::= { hsw3000c01v3Entry 198 }

		-- 1.3.6.1.4.1.10106.3.101291.1.1.199
		hsw3000c01v3SelOut1 OBJECT-TYPE
			SYNTAX HswOutput
			MAX-ACCESS read-only
			STATUS current
			DESCRIPTION
				"Output 1"
		::= { hsw3000c01v3Entry 199 }

		-- 1.3.6.1.4.1.10106.3.101291.1.1.200
		hsw3000c01v3SelOut1TrapEnable OBJECT-TYPE
			SYNTAX AlarmEnable
			MAX-ACCESS read-write
			STATUS current
			DESCRIPTION
				"Output 1 Trap Enable"
		::= { hsw3000c01v3Entry 200 }

		-- 1.3.6.1.4.1.10106.3.101291.1.1.201
		hsw3000c01v3SelOut2 OBJECT-TYPE
			SYNTAX HswOutput
			MAX-ACCESS read-only
			STATUS current
			DESCRIPTION
				"Output 2"
		::= { hsw3000c01v3Entry 201 }

		-- 1.3.6.1.4.1.10106.3.101291.1.1.202
		hsw3000c01v3SelOut2TrapEnable OBJECT-TYPE
			SYNTAX AlarmEnable
			MAX-ACCESS read-write
			STATUS current
			DESCRIPTION
				"Output 2 Trap Enable"
		::= { hsw3000c01v3Entry 202 }

		-- 1.3.6.1.4.1.10106.3.101291.1.1.203
		hsw3000c01v3EqualUmid OBJECT-TYPE
			SYNTAX UmidStatus
			MAX-ACCESS read-only
			STATUS current
			DESCRIPTION
				"Indicates if both  inputs have same UMID"
		::= { hsw3000c01v3Entry 203 }

		-- 1.3.6.1.4.1.10106.3.101291.1.1.204
		hsw3000c01v3EqualUmidTrapEnable OBJECT-TYPE
			SYNTAX AlarmEnable
			MAX-ACCESS read-write
			STATUS current
			DESCRIPTION
				"Indicates if both  inputs have same UMID Trap Enable"
		::= { hsw3000c01v3Entry 204 }

		-- 1.3.6.1.4.1.10106.3.101291.1.1.205
		hsw3000c01v3Gpi3Stat OBJECT-TYPE
			SYNTAX BitFail
			MAX-ACCESS read-only
			STATUS current
			DESCRIPTION
				"GPI1B status (used in remote control)"
		::= { hsw3000c01v3Entry 205 }

		-- 1.3.6.1.4.1.10106.3.101291.1.1.206
		hsw3000c01v3Gpi3StatTrapEnable OBJECT-TYPE
			SYNTAX AlarmEnable
			MAX-ACCESS read-write
			STATUS current
			DESCRIPTION
				"GPI1B status (used in remote control) Trap Enable"
		::= { hsw3000c01v3Entry 206 }

		-- 1.3.6.1.4.1.10106.3.101291.1.1.207
		hsw3000c01v3In1PhyFail OBJECT-TYPE
			SYNTAX BitFail
			MAX-ACCESS read-only
			STATUS current
			DESCRIPTION
				"Absence fail"
		::= { hsw3000c01v3Entry 207 }

		-- 1.3.6.1.4.1.10106.3.101291.1.1.208
		hsw3000c01v3In1PhyFailTrapEnable OBJECT-TYPE
			SYNTAX AlarmEnable
			MAX-ACCESS read-write
			STATUS current
			DESCRIPTION
				"Absence fail Trap Enable"
		::= { hsw3000c01v3Entry 208 }

		-- 1.3.6.1.4.1.10106.3.101291.1.1.209
		hsw3000c01v3In1FmtFail OBJECT-TYPE
			SYNTAX BitFail
			MAX-ACCESS read-only
			STATUS current
			DESCRIPTION
				"Format fail"
		::= { hsw3000c01v3Entry 209 }

		-- 1.3.6.1.4.1.10106.3.101291.1.1.210
		hsw3000c01v3In1FmtFailTrapEnable OBJECT-TYPE
			SYNTAX AlarmEnable
			MAX-ACCESS read-write
			STATUS current
			DESCRIPTION
				"Format fail Trap Enable"
		::= { hsw3000c01v3Entry 210 }

		-- 1.3.6.1.4.1.10106.3.101291.1.1.211
		hsw3000c01v3In1IncFail OBJECT-TYPE
			SYNTAX BitFail
			MAX-ACCESS read-only
			STATUS current
			DESCRIPTION
				"Incompatible format fail"
		::= { hsw3000c01v3Entry 211 }

		-- 1.3.6.1.4.1.10106.3.101291.1.1.212
		hsw3000c01v3In1IncFailTrapEnable OBJECT-TYPE
			SYNTAX AlarmEnable
			MAX-ACCESS read-write
			STATUS current
			DESCRIPTION
				"Incompatible format fail Trap Enable"
		::= { hsw3000c01v3Entry 212 }

		-- 1.3.6.1.4.1.10106.3.101291.1.1.213
		hsw3000c01v3In1GpiFail OBJECT-TYPE
			SYNTAX BitFail
			MAX-ACCESS read-only
			STATUS current
			DESCRIPTION
				"External GPI fail"
		::= { hsw3000c01v3Entry 213 }

		-- 1.3.6.1.4.1.10106.3.101291.1.1.214
		hsw3000c01v3In1GpiFailTrapEnable OBJECT-TYPE
			SYNTAX AlarmEnable
			MAX-ACCESS read-write
			STATUS current
			DESCRIPTION
				"External GPI fail Trap Enable"
		::= { hsw3000c01v3Entry 214 }

		-- 1.3.6.1.4.1.10106.3.101291.1.1.215
		hsw3000c01v3In1BlkFail OBJECT-TYPE
			SYNTAX BitFail
			MAX-ACCESS read-only
			STATUS current
			DESCRIPTION
				"Black signal fail"
		::= { hsw3000c01v3Entry 215 }

		-- 1.3.6.1.4.1.10106.3.101291.1.1.216
		hsw3000c01v3In1BlkFailTrapEnable OBJECT-TYPE
			SYNTAX AlarmEnable
			MAX-ACCESS read-write
			STATUS current
			DESCRIPTION
				"Black signal fail Trap Enable"
		::= { hsw3000c01v3Entry 216 }

		-- 1.3.6.1.4.1.10106.3.101291.1.1.217
		hsw3000c01v3In1FrzFail OBJECT-TYPE
			SYNTAX BitFail
			MAX-ACCESS read-only
			STATUS current
			DESCRIPTION
				"Freeze signal fail"
		::= { hsw3000c01v3Entry 217 }

		-- 1.3.6.1.4.1.10106.3.101291.1.1.218
		hsw3000c01v3In1FrzFailTrapEnable OBJECT-TYPE
			SYNTAX AlarmEnable
			MAX-ACCESS read-write
			STATUS current
			DESCRIPTION
				"Freeze signal fail Trap Enable"
		::= { hsw3000c01v3Entry 218 }

		-- 1.3.6.1.4.1.10106.3.101291.1.1.219
		hsw3000c01v3In1PatFail OBJECT-TYPE
			SYNTAX BitFail
			MAX-ACCESS read-only
			STATUS current
			DESCRIPTION
				"Video pattern fail"
		::= { hsw3000c01v3Entry 219 }

		-- 1.3.6.1.4.1.10106.3.101291.1.1.220
		hsw3000c01v3In1PatFailTrapEnable OBJECT-TYPE
			SYNTAX AlarmEnable
			MAX-ACCESS read-write
			STATUS current
			DESCRIPTION
				"Video pattern fail Trap Enable"
		::= { hsw3000c01v3Entry 220 }

		-- 1.3.6.1.4.1.10106.3.101291.1.1.221
		hsw3000c01v3In1CrcFail OBJECT-TYPE
			SYNTAX BitFail
			MAX-ACCESS read-only
			STATUS current
			DESCRIPTION
				"EDH/CRC fail"
		::= { hsw3000c01v3Entry 221 }

		-- 1.3.6.1.4.1.10106.3.101291.1.1.222
		hsw3000c01v3In1CrcFailTrapEnable OBJECT-TYPE
			SYNTAX AlarmEnable
			MAX-ACCESS read-write
			STATUS current
			DESCRIPTION
				"EDH/CRC fail Trap Enable"
		::= { hsw3000c01v3Entry 222 }

		-- 1.3.6.1.4.1.10106.3.101291.1.1.223
		hsw3000c01v3In1SilFail OBJECT-TYPE
			SYNTAX BitFail
			MAX-ACCESS read-only
			STATUS current
			DESCRIPTION
				"Audio silence fail"
		::= { hsw3000c01v3Entry 223 }

		-- 1.3.6.1.4.1.10106.3.101291.1.1.224
		hsw3000c01v3In1SilFailTrapEnable OBJECT-TYPE
			SYNTAX AlarmEnable
			MAX-ACCESS read-write
			STATUS current
			DESCRIPTION
				"Audio silence fail Trap Enable"
		::= { hsw3000c01v3Entry 224 }

		-- 1.3.6.1.4.1.10106.3.101291.1.1.225
		hsw3000c01v3In1OvrFail OBJECT-TYPE
			SYNTAX BitFail
			MAX-ACCESS read-only
			STATUS current
			DESCRIPTION
				"Audio overload fail"
		::= { hsw3000c01v3Entry 225 }

		-- 1.3.6.1.4.1.10106.3.101291.1.1.226
		hsw3000c01v3In1OvrFailTrapEnable OBJECT-TYPE
			SYNTAX AlarmEnable
			MAX-ACCESS read-write
			STATUS current
			DESCRIPTION
				"Audio overload fail Trap Enable"
		::= { hsw3000c01v3Entry 226 }

		-- 1.3.6.1.4.1.10106.3.101291.1.1.227
		hsw3000c01v3In1PhFail OBJECT-TYPE
			SYNTAX BitFail
			MAX-ACCESS read-only
			STATUS current
			DESCRIPTION
				"Audio phase fail"
		::= { hsw3000c01v3Entry 227 }

		-- 1.3.6.1.4.1.10106.3.101291.1.1.228
		hsw3000c01v3In1PhFailTrapEnable OBJECT-TYPE
			SYNTAX AlarmEnable
			MAX-ACCESS read-write
			STATUS current
			DESCRIPTION
				"Audio phase fail Trap Enable"
		::= { hsw3000c01v3Entry 228 }

		-- 1.3.6.1.4.1.10106.3.101291.1.1.229
		hsw3000c01v3In1PreFail OBJECT-TYPE
			SYNTAX BitFail
			MAX-ACCESS read-only
			STATUS current
			DESCRIPTION
				"Audio presence fail"
		::= { hsw3000c01v3Entry 229 }

		-- 1.3.6.1.4.1.10106.3.101291.1.1.230
		hsw3000c01v3In1PreFailTrapEnable OBJECT-TYPE
			SYNTAX AlarmEnable
			MAX-ACCESS read-write
			STATUS current
			DESCRIPTION
				"Audio presence fail Trap Enable"
		::= { hsw3000c01v3Entry 230 }

		-- 1.3.6.1.4.1.10106.3.101291.1.1.231
		hsw3000c01v3In2PhyFail OBJECT-TYPE
			SYNTAX BitFail
			MAX-ACCESS read-only
			STATUS current
			DESCRIPTION
				"Absence fail"
		::= { hsw3000c01v3Entry 231 }

		-- 1.3.6.1.4.1.10106.3.101291.1.1.232
		hsw3000c01v3In2PhyFailTrapEnable OBJECT-TYPE
			SYNTAX AlarmEnable
			MAX-ACCESS read-write
			STATUS current
			DESCRIPTION
				"Absence fail Trap Enable"
		::= { hsw3000c01v3Entry 232 }

		-- 1.3.6.1.4.1.10106.3.101291.1.1.233
		hsw3000c01v3In2FmtFail OBJECT-TYPE
			SYNTAX BitFail
			MAX-ACCESS read-only
			STATUS current
			DESCRIPTION
				"Format fail"
		::= { hsw3000c01v3Entry 233 }

		-- 1.3.6.1.4.1.10106.3.101291.1.1.234
		hsw3000c01v3In2FmtFailTrapEnable OBJECT-TYPE
			SYNTAX AlarmEnable
			MAX-ACCESS read-write
			STATUS current
			DESCRIPTION
				"Format fail Trap Enable"
		::= { hsw3000c01v3Entry 234 }

		-- 1.3.6.1.4.1.10106.3.101291.1.1.235
		hsw3000c01v3In2IncFail OBJECT-TYPE
			SYNTAX BitFail
			MAX-ACCESS read-only
			STATUS current
			DESCRIPTION
				"Incompatible format fail"
		::= { hsw3000c01v3Entry 235 }

		-- 1.3.6.1.4.1.10106.3.101291.1.1.236
		hsw3000c01v3In2IncFailTrapEnable OBJECT-TYPE
			SYNTAX AlarmEnable
			MAX-ACCESS read-write
			STATUS current
			DESCRIPTION
				"Incompatible format fail Trap Enable"
		::= { hsw3000c01v3Entry 236 }

		-- 1.3.6.1.4.1.10106.3.101291.1.1.237
		hsw3000c01v3In2GpiFail OBJECT-TYPE
			SYNTAX BitFail
			MAX-ACCESS read-only
			STATUS current
			DESCRIPTION
				"External GPI fail"
		::= { hsw3000c01v3Entry 237 }

		-- 1.3.6.1.4.1.10106.3.101291.1.1.238
		hsw3000c01v3In2GpiFailTrapEnable OBJECT-TYPE
			SYNTAX AlarmEnable
			MAX-ACCESS read-write
			STATUS current
			DESCRIPTION
				"External GPI fail Trap Enable"
		::= { hsw3000c01v3Entry 238 }

		-- 1.3.6.1.4.1.10106.3.101291.1.1.239
		hsw3000c01v3In2BlkFail OBJECT-TYPE
			SYNTAX BitFail
			MAX-ACCESS read-only
			STATUS current
			DESCRIPTION
				"Black signal fail"
		::= { hsw3000c01v3Entry 239 }

		-- 1.3.6.1.4.1.10106.3.101291.1.1.240
		hsw3000c01v3In2BlkFailTrapEnable OBJECT-TYPE
			SYNTAX AlarmEnable
			MAX-ACCESS read-write
			STATUS current
			DESCRIPTION
				"Black signal fail Trap Enable"
		::= { hsw3000c01v3Entry 240 }

		-- 1.3.6.1.4.1.10106.3.101291.1.1.241
		hsw3000c01v3In2FrzFail OBJECT-TYPE
			SYNTAX BitFail
			MAX-ACCESS read-only
			STATUS current
			DESCRIPTION
				"Freeze signal fail"
		::= { hsw3000c01v3Entry 241 }

		-- 1.3.6.1.4.1.10106.3.101291.1.1.242
		hsw3000c01v3In2FrzFailTrapEnable OBJECT-TYPE
			SYNTAX AlarmEnable
			MAX-ACCESS read-write
			STATUS current
			DESCRIPTION
				"Freeze signal fail Trap Enable"
		::= { hsw3000c01v3Entry 242 }

		-- 1.3.6.1.4.1.10106.3.101291.1.1.243
		hsw3000c01v3In2PatFail OBJECT-TYPE
			SYNTAX BitFail
			MAX-ACCESS read-only
			STATUS current
			DESCRIPTION
				"Video pattern fail"
		::= { hsw3000c01v3Entry 243 }

		-- 1.3.6.1.4.1.10106.3.101291.1.1.244
		hsw3000c01v3In2PatFailTrapEnable OBJECT-TYPE
			SYNTAX AlarmEnable
			MAX-ACCESS read-write
			STATUS current
			DESCRIPTION
				"Video pattern fail Trap Enable"
		::= { hsw3000c01v3Entry 244 }

		-- 1.3.6.1.4.1.10106.3.101291.1.1.245
		hsw3000c01v3In2CrcFail OBJECT-TYPE
			SYNTAX BitFail
			MAX-ACCESS read-only
			STATUS current
			DESCRIPTION
				"EDH/CRC fail"
		::= { hsw3000c01v3Entry 245 }

		-- 1.3.6.1.4.1.10106.3.101291.1.1.246
		hsw3000c01v3In2CrcFailTrapEnable OBJECT-TYPE
			SYNTAX AlarmEnable
			MAX-ACCESS read-write
			STATUS current
			DESCRIPTION
				"EDH/CRC fail Trap Enable"
		::= { hsw3000c01v3Entry 246 }

		-- 1.3.6.1.4.1.10106.3.101291.1.1.247
		hsw3000c01v3In2SilFail OBJECT-TYPE
			SYNTAX BitFail
			MAX-ACCESS read-only
			STATUS current
			DESCRIPTION
				"Audio silence fail"
		::= { hsw3000c01v3Entry 247 }

		-- 1.3.6.1.4.1.10106.3.101291.1.1.248
		hsw3000c01v3In2SilFailTrapEnable OBJECT-TYPE
			SYNTAX AlarmEnable
			MAX-ACCESS read-write
			STATUS current
			DESCRIPTION
				"Audio silence fail Trap Enable"
		::= { hsw3000c01v3Entry 248 }

		-- 1.3.6.1.4.1.10106.3.101291.1.1.249
		hsw3000c01v3In2OvrFail OBJECT-TYPE
			SYNTAX BitFail
			MAX-ACCESS read-only
			STATUS current
			DESCRIPTION
				"Audio overload fail"
		::= { hsw3000c01v3Entry 249 }

		-- 1.3.6.1.4.1.10106.3.101291.1.1.250
		hsw3000c01v3In2OvrFailTrapEnable OBJECT-TYPE
			SYNTAX AlarmEnable
			MAX-ACCESS read-write
			STATUS current
			DESCRIPTION
				"Audio overload fail Trap Enable"
		::= { hsw3000c01v3Entry 250 }

		-- 1.3.6.1.4.1.10106.3.101291.1.1.251
		hsw3000c01v3In2PhFail OBJECT-TYPE
			SYNTAX BitFail
			MAX-ACCESS read-only
			STATUS current
			DESCRIPTION
				"Audio phase fail"
		::= { hsw3000c01v3Entry 251 }

		-- 1.3.6.1.4.1.10106.3.101291.1.1.252
		hsw3000c01v3In2PhFailTrapEnable OBJECT-TYPE
			SYNTAX AlarmEnable
			MAX-ACCESS read-write
			STATUS current
			DESCRIPTION
				"Audio phase fail Trap Enable"
		::= { hsw3000c01v3Entry 252 }

		-- 1.3.6.1.4.1.10106.3.101291.1.1.253
		hsw3000c01v3In2PreFail OBJECT-TYPE
			SYNTAX BitFail
			MAX-ACCESS read-only
			STATUS current
			DESCRIPTION
				"Audio presence fail"
		::= { hsw3000c01v3Entry 253 }

		-- 1.3.6.1.4.1.10106.3.101291.1.1.254
		hsw3000c01v3In2PreFailTrapEnable OBJECT-TYPE
			SYNTAX AlarmEnable
			MAX-ACCESS read-write
			STATUS current
			DESCRIPTION
				"Audio presence fail Trap Enable"
		::= { hsw3000c01v3Entry 254 }

		-- 1.3.6.1.4.1.10106.3.101291.1.1.255
		hsw3000c01v3RefFail OBJECT-TYPE
			SYNTAX BitFail
			MAX-ACCESS read-only
			STATUS current
			DESCRIPTION
				"Reference absence fail"
		::= { hsw3000c01v3Entry 255 }

		-- 1.3.6.1.4.1.10106.3.101291.1.1.256
		hsw3000c01v3RefFailTrapEnable OBJECT-TYPE
			SYNTAX AlarmEnable
			MAX-ACCESS read-write
			STATUS current
			DESCRIPTION
				"Reference absence fail Trap Enable"
		::= { hsw3000c01v3Entry 256 }

		-- 1.3.6.1.4.1.10106.3.101291.1.1.257
		hsw3000c01v3LockFail OBJECT-TYPE
			SYNTAX BitFail
			MAX-ACCESS read-only
			STATUS current
			DESCRIPTION
				"Reference unlock fail"
		::= { hsw3000c01v3Entry 257 }

		-- 1.3.6.1.4.1.10106.3.101291.1.1.258
		hsw3000c01v3LockFailTrapEnable OBJECT-TYPE
			SYNTAX AlarmEnable
			MAX-ACCESS read-write
			STATUS current
			DESCRIPTION
				"Reference unlock fail Trap Enable"
		::= { hsw3000c01v3Entry 258 }

		-- 1.3.6.1.4.1.10106.3.101291.1.1.259
		hsw3000c01v3BliGpiFail OBJECT-TYPE
			SYNTAX BitFail
			MAX-ACCESS read-only
			STATUS current
			DESCRIPTION
				"GPI2B status (used in blind halfauto mode)"
		::= { hsw3000c01v3Entry 259 }

		-- 1.3.6.1.4.1.10106.3.101291.1.1.261
		hsw3000c01v3In1Format OBJECT-TYPE
			SYNTAX SdiHd3gFmt3
			MAX-ACCESS read-only
			STATUS current
			DESCRIPTION
				"Input format"
		::= { hsw3000c01v3Entry 261 }

		-- 1.3.6.1.4.1.10106.3.101291.1.1.262
		hsw3000c01v3In1FormatTrapEnable OBJECT-TYPE
			SYNTAX AlarmEnable
			MAX-ACCESS read-write
			STATUS current
			DESCRIPTION
				"Input format Trap Enable"
		::= { hsw3000c01v3Entry 262 }

		-- 1.3.6.1.4.1.10106.3.101291.1.1.263
		hsw3000c01v3In2Format OBJECT-TYPE
			SYNTAX SdiHd3gFmt3
			MAX-ACCESS read-only
			STATUS current
			DESCRIPTION
				"Input format"
		::= { hsw3000c01v3Entry 263 }

		-- 1.3.6.1.4.1.10106.3.101291.1.1.264
		hsw3000c01v3In2FormatTrapEnable OBJECT-TYPE
			SYNTAX AlarmEnable
			MAX-ACCESS read-write
			STATUS current
			DESCRIPTION
				"Input format Trap Enable"
		::= { hsw3000c01v3Entry 264 }

		-- 1.3.6.1.4.1.10106.3.101291.1.1.265
		hsw3000c01v3RefFormat OBJECT-TYPE
			SYNTAX SdiHd3gFmt3
			MAX-ACCESS read-only
			STATUS current
			DESCRIPTION
				"Reference format"
		::= { hsw3000c01v3Entry 265 }

		-- 1.3.6.1.4.1.10106.3.101291.1.1.266
		hsw3000c01v3RefFormatTrapEnable OBJECT-TYPE
			SYNTAX AlarmEnable
			MAX-ACCESS read-write
			STATUS current
			DESCRIPTION
				"Reference format Trap Enable"
		::= { hsw3000c01v3Entry 266 }

		-- 1.3.6.1.4.1.10106.3.101291.1.1.267
		hsw3000c01v3In1PidPres OBJECT-TYPE
			SYNTAX Bit0No1Yes
			MAX-ACCESS read-only
			STATUS current
			DESCRIPTION
				"Indicates if there are PID packets"
		::= { hsw3000c01v3Entry 267 }

		-- 1.3.6.1.4.1.10106.3.101291.1.1.269
		hsw3000c01v3In2PidPres OBJECT-TYPE
			SYNTAX Bit0No1Yes
			MAX-ACCESS read-only
			STATUS current
			DESCRIPTION
				"Indicates if there are PID packets"
		::= { hsw3000c01v3Entry 269 }

		-- 1.3.6.1.4.1.10106.3.101291.1.1.271
		hsw3000c01v3In1UmidPres OBJECT-TYPE
			SYNTAX Bit0No1Yes
			MAX-ACCESS read-only
			STATUS current
			DESCRIPTION
				"Indicates if there are UMID packets"
		::= { hsw3000c01v3Entry 271 }

		-- 1.3.6.1.4.1.10106.3.101291.1.1.273
		hsw3000c01v3In2UmidPres OBJECT-TYPE
			SYNTAX Bit0No1Yes
			MAX-ACCESS read-only
			STATUS current
			DESCRIPTION
				"Indicates if there are UMID packets"
		::= { hsw3000c01v3Entry 273 }

		-- 1.3.6.1.4.1.10106.3.101291.1.1.275
		hsw3000c01v3In1Grp1Pres OBJECT-TYPE
			SYNTAX Bit0No1Yes
			MAX-ACCESS read-only
			STATUS current
			DESCRIPTION
				"Audio group 1 packet presence"
		::= { hsw3000c01v3Entry 275 }

		-- 1.3.6.1.4.1.10106.3.101291.1.1.276
		hsw3000c01v3In1Grp1PresTrapEnable OBJECT-TYPE
			SYNTAX AlarmEnable
			MAX-ACCESS read-write
			STATUS current
			DESCRIPTION
				"Audio group 1 packet presence Trap Enable"
		::= { hsw3000c01v3Entry 276 }

		-- 1.3.6.1.4.1.10106.3.101291.1.1.277
		hsw3000c01v3In1Grp2Pres OBJECT-TYPE
			SYNTAX Bit0No1Yes
			MAX-ACCESS read-only
			STATUS current
			DESCRIPTION
				"Audio group 2 packet presence"
		::= { hsw3000c01v3Entry 277 }

		-- 1.3.6.1.4.1.10106.3.101291.1.1.278
		hsw3000c01v3In1Grp2PresTrapEnable OBJECT-TYPE
			SYNTAX AlarmEnable
			MAX-ACCESS read-write
			STATUS current
			DESCRIPTION
				"Audio group 2 packet presence Trap Enable"
		::= { hsw3000c01v3Entry 278 }

		-- 1.3.6.1.4.1.10106.3.101291.1.1.279
		hsw3000c01v3In1Grp3Pres OBJECT-TYPE
			SYNTAX Bit0No1Yes
			MAX-ACCESS read-only
			STATUS current
			DESCRIPTION
				"Audio group 3 packet presence"
		::= { hsw3000c01v3Entry 279 }

		-- 1.3.6.1.4.1.10106.3.101291.1.1.280
		hsw3000c01v3In1Grp3PresTrapEnable OBJECT-TYPE
			SYNTAX AlarmEnable
			MAX-ACCESS read-write
			STATUS current
			DESCRIPTION
				"Audio group 3 packet presence Trap Enable"
		::= { hsw3000c01v3Entry 280 }

		-- 1.3.6.1.4.1.10106.3.101291.1.1.281
		hsw3000c01v3In1Grp4Pres OBJECT-TYPE
			SYNTAX Bit0No1Yes
			MAX-ACCESS read-only
			STATUS current
			DESCRIPTION
				"Audio group 4 packet presence"
		::= { hsw3000c01v3Entry 281 }

		-- 1.3.6.1.4.1.10106.3.101291.1.1.282
		hsw3000c01v3In1Grp4PresTrapEnable OBJECT-TYPE
			SYNTAX AlarmEnable
			MAX-ACCESS read-write
			STATUS current
			DESCRIPTION
				"Audio group 4 packet presence Trap Enable"
		::= { hsw3000c01v3Entry 282 }

		-- 1.3.6.1.4.1.10106.3.101291.1.1.283
		hsw3000c01v3In1Grp1P0Stat OBJECT-TYPE
			SYNTAX AudioStatus
			MAX-ACCESS read-only
			STATUS current
			DESCRIPTION
				"Audio group 1 pair 0 status"
		::= { hsw3000c01v3Entry 283 }

		-- 1.3.6.1.4.1.10106.3.101291.1.1.284
		hsw3000c01v3In1Grp1P0StatTrapEnable OBJECT-TYPE
			SYNTAX AlarmEnable
			MAX-ACCESS read-write
			STATUS current
			DESCRIPTION
				"Audio group 1 pair 0 status Trap Enable"
		::= { hsw3000c01v3Entry 284 }

		-- 1.3.6.1.4.1.10106.3.101291.1.1.285
		hsw3000c01v3In1Grp1P1Stat OBJECT-TYPE
			SYNTAX AudioStatus
			MAX-ACCESS read-only
			STATUS current
			DESCRIPTION
				"Audio group 1 pair 1 status"
		::= { hsw3000c01v3Entry 285 }

		-- 1.3.6.1.4.1.10106.3.101291.1.1.286
		hsw3000c01v3In1Grp1P1StatTrapEnable OBJECT-TYPE
			SYNTAX AlarmEnable
			MAX-ACCESS read-write
			STATUS current
			DESCRIPTION
				"Audio group 1 pair 1 status Trap Enable"
		::= { hsw3000c01v3Entry 286 }

		-- 1.3.6.1.4.1.10106.3.101291.1.1.287
		hsw3000c01v3In1Grp2P0Stat OBJECT-TYPE
			SYNTAX AudioStatus
			MAX-ACCESS read-only
			STATUS current
			DESCRIPTION
				"Audio group 2 pair 0 status"
		::= { hsw3000c01v3Entry 287 }

		-- 1.3.6.1.4.1.10106.3.101291.1.1.288
		hsw3000c01v3In1Grp2P0StatTrapEnable OBJECT-TYPE
			SYNTAX AlarmEnable
			MAX-ACCESS read-write
			STATUS current
			DESCRIPTION
				"Audio group 2 pair 0 status Trap Enable"
		::= { hsw3000c01v3Entry 288 }

		-- 1.3.6.1.4.1.10106.3.101291.1.1.289
		hsw3000c01v3In1Grp2P1Stat OBJECT-TYPE
			SYNTAX AudioStatus
			MAX-ACCESS read-only
			STATUS current
			DESCRIPTION
				"Audio group 2 pair 1 status"
		::= { hsw3000c01v3Entry 289 }

		-- 1.3.6.1.4.1.10106.3.101291.1.1.290
		hsw3000c01v3In1Grp2P1StatTrapEnable OBJECT-TYPE
			SYNTAX AlarmEnable
			MAX-ACCESS read-write
			STATUS current
			DESCRIPTION
				"Audio group 2 pair 1 status Trap Enable"
		::= { hsw3000c01v3Entry 290 }

		-- 1.3.6.1.4.1.10106.3.101291.1.1.291
		hsw3000c01v3In1Grp3P0Stat OBJECT-TYPE
			SYNTAX AudioStatus
			MAX-ACCESS read-only
			STATUS current
			DESCRIPTION
				"Audio group 3 pair 0 status"
		::= { hsw3000c01v3Entry 291 }

		-- 1.3.6.1.4.1.10106.3.101291.1.1.292
		hsw3000c01v3In1Grp3P0StatTrapEnable OBJECT-TYPE
			SYNTAX AlarmEnable
			MAX-ACCESS read-write
			STATUS current
			DESCRIPTION
				"Audio group 3 pair 0 status Trap Enable"
		::= { hsw3000c01v3Entry 292 }

		-- 1.3.6.1.4.1.10106.3.101291.1.1.293
		hsw3000c01v3In1Grp3P1Stat OBJECT-TYPE
			SYNTAX AudioStatus
			MAX-ACCESS read-only
			STATUS current
			DESCRIPTION
				"Audio group 3 pair 1 status"
		::= { hsw3000c01v3Entry 293 }

		-- 1.3.6.1.4.1.10106.3.101291.1.1.294
		hsw3000c01v3In1Grp3P1StatTrapEnable OBJECT-TYPE
			SYNTAX AlarmEnable
			MAX-ACCESS read-write
			STATUS current
			DESCRIPTION
				"Audio group 3 pair 1 status Trap Enable"
		::= { hsw3000c01v3Entry 294 }

		-- 1.3.6.1.4.1.10106.3.101291.1.1.295
		hsw3000c01v3In1Grp4P0Stat OBJECT-TYPE
			SYNTAX AudioStatus
			MAX-ACCESS read-only
			STATUS current
			DESCRIPTION
				"Audio group 4 pair 0 status"
		::= { hsw3000c01v3Entry 295 }

		-- 1.3.6.1.4.1.10106.3.101291.1.1.296
		hsw3000c01v3In1Grp4P0StatTrapEnable OBJECT-TYPE
			SYNTAX AlarmEnable
			MAX-ACCESS read-write
			STATUS current
			DESCRIPTION
				"Audio group 4 pair 0 status Trap Enable"
		::= { hsw3000c01v3Entry 296 }

		-- 1.3.6.1.4.1.10106.3.101291.1.1.297
		hsw3000c01v3In1Grp4P1Stat OBJECT-TYPE
			SYNTAX AudioStatus
			MAX-ACCESS read-only
			STATUS current
			DESCRIPTION
				"Audio group 4 pair 1 status"
		::= { hsw3000c01v3Entry 297 }

		-- 1.3.6.1.4.1.10106.3.101291.1.1.298
		hsw3000c01v3In1Grp4P1StatTrapEnable OBJECT-TYPE
			SYNTAX AlarmEnable
			MAX-ACCESS read-write
			STATUS current
			DESCRIPTION
				"Audio group 4 pair 1 status Trap Enable"
		::= { hsw3000c01v3Entry 298 }

		-- 1.3.6.1.4.1.10106.3.101291.1.1.299
		hsw3000c01v3In2Grp1Pres OBJECT-TYPE
			SYNTAX Bit0No1Yes
			MAX-ACCESS read-only
			STATUS current
			DESCRIPTION
				"Audio group 1 packet presence"
		::= { hsw3000c01v3Entry 299 }

		-- 1.3.6.1.4.1.10106.3.101291.1.1.300
		hsw3000c01v3In2Grp1PresTrapEnable OBJECT-TYPE
			SYNTAX AlarmEnable
			MAX-ACCESS read-write
			STATUS current
			DESCRIPTION
				"Audio group 1 packet presence Trap Enable"
		::= { hsw3000c01v3Entry 300 }

		-- 1.3.6.1.4.1.10106.3.101291.1.1.301
		hsw3000c01v3In2Grp2Pres OBJECT-TYPE
			SYNTAX Bit0No1Yes
			MAX-ACCESS read-only
			STATUS current
			DESCRIPTION
				"Audio group 2 packet presence"
		::= { hsw3000c01v3Entry 301 }

		-- 1.3.6.1.4.1.10106.3.101291.1.1.302
		hsw3000c01v3In2Grp2PresTrapEnable OBJECT-TYPE
			SYNTAX AlarmEnable
			MAX-ACCESS read-write
			STATUS current
			DESCRIPTION
				"Audio group 2 packet presence Trap Enable"
		::= { hsw3000c01v3Entry 302 }

		-- 1.3.6.1.4.1.10106.3.101291.1.1.303
		hsw3000c01v3In2Grp3Pres OBJECT-TYPE
			SYNTAX Bit0No1Yes
			MAX-ACCESS read-only
			STATUS current
			DESCRIPTION
				"Audio group 3 packet presence"
		::= { hsw3000c01v3Entry 303 }

		-- 1.3.6.1.4.1.10106.3.101291.1.1.304
		hsw3000c01v3In2Grp3PresTrapEnable OBJECT-TYPE
			SYNTAX AlarmEnable
			MAX-ACCESS read-write
			STATUS current
			DESCRIPTION
				"Audio group 3 packet presence Trap Enable"
		::= { hsw3000c01v3Entry 304 }

		-- 1.3.6.1.4.1.10106.3.101291.1.1.305
		hsw3000c01v3In2Grp4Pres OBJECT-TYPE
			SYNTAX Bit0No1Yes
			MAX-ACCESS read-only
			STATUS current
			DESCRIPTION
				"Audio group 4 packet presence"
		::= { hsw3000c01v3Entry 305 }

		-- 1.3.6.1.4.1.10106.3.101291.1.1.306
		hsw3000c01v3In2Grp4PresTrapEnable OBJECT-TYPE
			SYNTAX AlarmEnable
			MAX-ACCESS read-write
			STATUS current
			DESCRIPTION
				"Audio group 4 packet presence Trap Enable"
		::= { hsw3000c01v3Entry 306 }

		-- 1.3.6.1.4.1.10106.3.101291.1.1.307
		hsw3000c01v3In2Grp1P0Stat OBJECT-TYPE
			SYNTAX AudioStatus
			MAX-ACCESS read-only
			STATUS current
			DESCRIPTION
				"Audio group 1 pair 0 status"
		::= { hsw3000c01v3Entry 307 }

		-- 1.3.6.1.4.1.10106.3.101291.1.1.308
		hsw3000c01v3In2Grp1P0StatTrapEnable OBJECT-TYPE
			SYNTAX AlarmEnable
			MAX-ACCESS read-write
			STATUS current
			DESCRIPTION
				"Audio group 1 pair 0 status Trap Enable"
		::= { hsw3000c01v3Entry 308 }

		-- 1.3.6.1.4.1.10106.3.101291.1.1.309
		hsw3000c01v3In2Grp1P1Stat OBJECT-TYPE
			SYNTAX AudioStatus
			MAX-ACCESS read-only
			STATUS current
			DESCRIPTION
				"Audio group 1 pair 1 status"
		::= { hsw3000c01v3Entry 309 }

		-- 1.3.6.1.4.1.10106.3.101291.1.1.310
		hsw3000c01v3In2Grp1P1StatTrapEnable OBJECT-TYPE
			SYNTAX AlarmEnable
			MAX-ACCESS read-write
			STATUS current
			DESCRIPTION
				"Audio group 1 pair 1 status Trap Enable"
		::= { hsw3000c01v3Entry 310 }

		-- 1.3.6.1.4.1.10106.3.101291.1.1.311
		hsw3000c01v3In2Grp2P0Stat OBJECT-TYPE
			SYNTAX AudioStatus
			MAX-ACCESS read-only
			STATUS current
			DESCRIPTION
				"Audio group 2 pair 0 status"
		::= { hsw3000c01v3Entry 311 }

		-- 1.3.6.1.4.1.10106.3.101291.1.1.312
		hsw3000c01v3In2Grp2P0StatTrapEnable OBJECT-TYPE
			SYNTAX AlarmEnable
			MAX-ACCESS read-write
			STATUS current
			DESCRIPTION
				"Audio group 2 pair 0 status Trap Enable"
		::= { hsw3000c01v3Entry 312 }

		-- 1.3.6.1.4.1.10106.3.101291.1.1.313
		hsw3000c01v3In2Grp2P1Stat OBJECT-TYPE
			SYNTAX AudioStatus
			MAX-ACCESS read-only
			STATUS current
			DESCRIPTION
				"Audio group 2 pair 1status"
		::= { hsw3000c01v3Entry 313 }

		-- 1.3.6.1.4.1.10106.3.101291.1.1.314
		hsw3000c01v3In2Grp2P1StatTrapEnable OBJECT-TYPE
			SYNTAX AlarmEnable
			MAX-ACCESS read-write
			STATUS current
			DESCRIPTION
				"Audio group 2 pair 1status Trap Enable"
		::= { hsw3000c01v3Entry 314 }

		-- 1.3.6.1.4.1.10106.3.101291.1.1.315
		hsw3000c01v3In2Grp3P0Stat OBJECT-TYPE
			SYNTAX AudioStatus
			MAX-ACCESS read-only
			STATUS current
			DESCRIPTION
				"Audio group 3 pair 0 status"
		::= { hsw3000c01v3Entry 315 }

		-- 1.3.6.1.4.1.10106.3.101291.1.1.316
		hsw3000c01v3In2Grp3P0StatTrapEnable OBJECT-TYPE
			SYNTAX AlarmEnable
			MAX-ACCESS read-write
			STATUS current
			DESCRIPTION
				"Audio group 3 pair 0 status Trap Enable"
		::= { hsw3000c01v3Entry 316 }

		-- 1.3.6.1.4.1.10106.3.101291.1.1.317
		hsw3000c01v3In2Grp3P1Stat OBJECT-TYPE
			SYNTAX AudioStatus
			MAX-ACCESS read-only
			STATUS current
			DESCRIPTION
				"Audio group 3 pair 1 status"
		::= { hsw3000c01v3Entry 317 }

		-- 1.3.6.1.4.1.10106.3.101291.1.1.318
		hsw3000c01v3In2Grp3P1StatTrapEnable OBJECT-TYPE
			SYNTAX AlarmEnable
			MAX-ACCESS read-write
			STATUS current
			DESCRIPTION
				"Audio group 3 pair 1 status Trap Enable"
		::= { hsw3000c01v3Entry 318 }

		-- 1.3.6.1.4.1.10106.3.101291.1.1.319
		hsw3000c01v3In2Grp4P0Stat OBJECT-TYPE
			SYNTAX AudioStatus
			MAX-ACCESS read-only
			STATUS current
			DESCRIPTION
				"Audio group 4 pair 0 status"
		::= { hsw3000c01v3Entry 319 }

		-- 1.3.6.1.4.1.10106.3.101291.1.1.320
		hsw3000c01v3In2Grp4P0StatTrapEnable OBJECT-TYPE
			SYNTAX AlarmEnable
			MAX-ACCESS read-write
			STATUS current
			DESCRIPTION
				"Audio group 4 pair 0 status Trap Enable"
		::= { hsw3000c01v3Entry 320 }

		-- 1.3.6.1.4.1.10106.3.101291.1.1.321
		hsw3000c01v3In2Grp4P1Stat OBJECT-TYPE
			SYNTAX AudioStatus
			MAX-ACCESS read-only
			STATUS current
			DESCRIPTION
				"Audio group 4 pair 1 status"
		::= { hsw3000c01v3Entry 321 }

		-- 1.3.6.1.4.1.10106.3.101291.1.1.322
		hsw3000c01v3In2Grp4P1StatTrapEnable OBJECT-TYPE
			SYNTAX AlarmEnable
			MAX-ACCESS read-write
			STATUS current
			DESCRIPTION
				"Audio group 4 pair 1 status Trap Enable"
		::= { hsw3000c01v3Entry 322 }

		-- 1.3.6.1.4.1.10106.3.101291.1.1.323
		hsw3000c01v3In1WssStat OBJECT-TYPE
			SYNTAX AfdInfo
			MAX-ACCESS read-only
			STATUS current
			DESCRIPTION
				"WSS information"
		::= { hsw3000c01v3Entry 323 }

		-- 1.3.6.1.4.1.10106.3.101291.1.1.324
		hsw3000c01v3In1WssStatTrapEnable OBJECT-TYPE
			SYNTAX AlarmEnable
			MAX-ACCESS read-write
			STATUS current
			DESCRIPTION
				"WSS information Trap Enable"
		::= { hsw3000c01v3Entry 324 }

		-- 1.3.6.1.4.1.10106.3.101291.1.1.325
		hsw3000c01v3In1ViiStat OBJECT-TYPE
			SYNTAX AfdInfo
			MAX-ACCESS read-only
			STATUS current
			DESCRIPTION
				"VII information"
		::= { hsw3000c01v3Entry 325 }

		-- 1.3.6.1.4.1.10106.3.101291.1.1.326
		hsw3000c01v3In1ViiStatTrapEnable OBJECT-TYPE
			SYNTAX AlarmEnable
			MAX-ACCESS read-write
			STATUS current
			DESCRIPTION
				"VII information Trap Enable"
		::= { hsw3000c01v3Entry 326 }

		-- 1.3.6.1.4.1.10106.3.101291.1.1.327
		hsw3000c01v3In12016Stat OBJECT-TYPE
			SYNTAX AfdInfo
			MAX-ACCESS read-only
			STATUS current
			DESCRIPTION
				"SMPTE 2016 information"
		::= { hsw3000c01v3Entry 327 }

		-- 1.3.6.1.4.1.10106.3.101291.1.1.328
		hsw3000c01v3In12016StatTrapEnable OBJECT-TYPE
			SYNTAX AlarmEnable
			MAX-ACCESS read-write
			STATUS current
			DESCRIPTION
				"SMPTE 2016 information Trap Enable"
		::= { hsw3000c01v3Entry 328 }

		-- 1.3.6.1.4.1.10106.3.101291.1.1.329
		hsw3000c01v3In2WssStat OBJECT-TYPE
			SYNTAX AfdInfo
			MAX-ACCESS read-only
			STATUS current
			DESCRIPTION
				"WSS information"
		::= { hsw3000c01v3Entry 329 }

		-- 1.3.6.1.4.1.10106.3.101291.1.1.330
		hsw3000c01v3In2WssStatTrapEnable OBJECT-TYPE
			SYNTAX AlarmEnable
			MAX-ACCESS read-write
			STATUS current
			DESCRIPTION
				"WSS information Trap Enable"
		::= { hsw3000c01v3Entry 330 }

		-- 1.3.6.1.4.1.10106.3.101291.1.1.331
		hsw3000c01v3In2ViiStat OBJECT-TYPE
			SYNTAX AfdInfo
			MAX-ACCESS read-only
			STATUS current
			DESCRIPTION
				"VII information"
		::= { hsw3000c01v3Entry 331 }

		-- 1.3.6.1.4.1.10106.3.101291.1.1.332
		hsw3000c01v3In2ViiStatTrapEnable OBJECT-TYPE
			SYNTAX AlarmEnable
			MAX-ACCESS read-write
			STATUS current
			DESCRIPTION
				"VII information Trap Enable"
		::= { hsw3000c01v3Entry 332 }

		-- 1.3.6.1.4.1.10106.3.101291.1.1.333
		hsw3000c01v3In22016Stat OBJECT-TYPE
			SYNTAX AfdInfo
			MAX-ACCESS read-only
			STATUS current
			DESCRIPTION
				"SMPTE 2016 information"
		::= { hsw3000c01v3Entry 333 }

		-- 1.3.6.1.4.1.10106.3.101291.1.1.334
		hsw3000c01v3In22016StatTrapEnable OBJECT-TYPE
			SYNTAX AlarmEnable
			MAX-ACCESS read-write
			STATUS current
			DESCRIPTION
				"SMPTE 2016 information Trap Enable"
		::= { hsw3000c01v3Entry 334 }

		-- 1.3.6.1.4.1.10106.3.101291.1.1.335
		hsw3000c01v3In1TxtLinLow OBJECT-TYPE
			SYNTAX Bit0No1Yes
			MAX-ACCESS read-only
			STATUS current
			DESCRIPTION
				"Low level of teletext lines"
		::= { hsw3000c01v3Entry 335 }

		-- 1.3.6.1.4.1.10106.3.101291.1.1.336
		hsw3000c01v3In1TxtLinLowTrapEnable OBJECT-TYPE
			SYNTAX AlarmEnable
			MAX-ACCESS read-write
			STATUS current
			DESCRIPTION
				"Low level of teletext lines Trap Enable"
		::= { hsw3000c01v3Entry 336 }

		-- 1.3.6.1.4.1.10106.3.101291.1.1.337
		hsw3000c01v3In1TxtLin1s OBJECT-TYPE
			SYNTAX Uint11
			MAX-ACCESS read-only
			STATUS current
			DESCRIPTION
				"Number of teletext lines in last second"
		::= { hsw3000c01v3Entry 337 }

		-- 1.3.6.1.4.1.10106.3.101291.1.1.339
		hsw3000c01v3In2TxtLinLow OBJECT-TYPE
			SYNTAX Bit0No1Yes
			MAX-ACCESS read-only
			STATUS current
			DESCRIPTION
				"Low level of teletext lines"
		::= { hsw3000c01v3Entry 339 }

		-- 1.3.6.1.4.1.10106.3.101291.1.1.340
		hsw3000c01v3In2TxtLinLowTrapEnable OBJECT-TYPE
			SYNTAX AlarmEnable
			MAX-ACCESS read-write
			STATUS current
			DESCRIPTION
				"Low level of teletext lines Trap Enable"
		::= { hsw3000c01v3Entry 340 }

		-- 1.3.6.1.4.1.10106.3.101291.1.1.341
		hsw3000c01v3In2TxtLin1s OBJECT-TYPE
			SYNTAX Uint11
			MAX-ACCESS read-only
			STATUS current
			DESCRIPTION
				"Number of teletext lines in last second"
		::= { hsw3000c01v3Entry 341 }

		-- 1.3.6.1.4.1.10106.3.101291.1.1.343
		hsw3000c01v3SerialNo OBJECT-TYPE
			SYNTAX SerialNo
			MAX-ACCESS read-only
			STATUS current
			DESCRIPTION
				"Serial number"
		::= { hsw3000c01v3Entry 343 }

		-- 1.3.6.1.4.1.10106.3.101291.1.1.345
		hsw3000c01v3GpoMode OBJECT-TYPE
			SYNTAX Bit0No1Yes
			MAX-ACCESS read-write
			STATUS current
			DESCRIPTION
				"Enable GPO mode that activates a GPO when a fail is detected in its corresponding input"
		::= { hsw3000c01v3Entry 345 }

		-- 1.3.6.1.4.1.10106.3.101291.1.1.347
		hsw3000c01v3DePer2IncIn1 OBJECT-TYPE
			SYNTAX Bit0Dis1Ena
			MAX-ACCESS read-write
			STATUS current
			DESCRIPTION
				"Allows increasing deactivation time of timing 2 for inpu1 in 500ms"
		::= { hsw3000c01v3Entry 347 }

		-- 1.3.6.1.4.1.10106.3.101291.1.1.349
		hsw3000c01v3DePer2IncIn2 OBJECT-TYPE
			SYNTAX Bit0Dis1Ena
			MAX-ACCESS read-write
			STATUS current
			DESCRIPTION
				"Allows increasing deactivation time of timing 2 for inpu2 in 500ms"
		::= { hsw3000c01v3Entry 349 }

		-- 1.3.6.1.4.1.10106.3.101291.1.1.351
		hsw3000c01v3FrzToBckTime OBJECT-TYPE
			SYNTAX TimeS2
			MAX-ACCESS read-write
			STATUS current
			DESCRIPTION
				"Freeze to black timeout"
		::= { hsw3000c01v3Entry 351 }

		-- 1.3.6.1.4.1.10106.3.101291.1.1.353
		hsw3000c01v3In1WssCod OBJECT-TYPE
			SYNTAX Code4Bit
			MAX-ACCESS read-only
			STATUS current
			DESCRIPTION
				"WSS group 1 data  (b3-b0)"
		::= { hsw3000c01v3Entry 353 }

		-- 1.3.6.1.4.1.10106.3.101291.1.1.354
		hsw3000c01v3In1WssCodTrapEnable OBJECT-TYPE
			SYNTAX AlarmEnable
			MAX-ACCESS read-write
			STATUS current
			DESCRIPTION
				"WSS group 1 data  (b3-b0) Trap Enable"
		::= { hsw3000c01v3Entry 354 }

		-- 1.3.6.1.4.1.10106.3.101291.1.1.355
		hsw3000c01v3In1ViiAfdCod OBJECT-TYPE
			SYNTAX Code4Bit
			MAX-ACCESS read-only
			STATUS current
			DESCRIPTION
				"VII AFD code (a3-a0)"
		::= { hsw3000c01v3Entry 355 }

		-- 1.3.6.1.4.1.10106.3.101291.1.1.356
		hsw3000c01v3In1ViiAfdCodTrapEnable OBJECT-TYPE
			SYNTAX AlarmEnable
			MAX-ACCESS read-write
			STATUS current
			DESCRIPTION
				"VII AFD code (a3-a0) Trap Enable"
		::= { hsw3000c01v3Entry 356 }

		-- 1.3.6.1.4.1.10106.3.101291.1.1.357
		hsw3000c01v3In12016AfdCod OBJECT-TYPE
			SYNTAX Code4Bit
			MAX-ACCESS read-only
			STATUS current
			DESCRIPTION
				"SMPTE 2016 AFD code (a3-a0)"
		::= { hsw3000c01v3Entry 357 }

		-- 1.3.6.1.4.1.10106.3.101291.1.1.358
		hsw3000c01v3In12016AfdCodTrapEnable OBJECT-TYPE
			SYNTAX AlarmEnable
			MAX-ACCESS read-write
			STATUS current
			DESCRIPTION
				"SMPTE 2016 AFD code (a3-a0) Trap Enable"
		::= { hsw3000c01v3Entry 358 }

		-- 1.3.6.1.4.1.10106.3.101291.1.1.359
		hsw3000c01v3In2WssCod OBJECT-TYPE
			SYNTAX Code4Bit
			MAX-ACCESS read-only
			STATUS current
			DESCRIPTION
				"WSS group 1 data  (b3-b0)"
		::= { hsw3000c01v3Entry 359 }

		-- 1.3.6.1.4.1.10106.3.101291.1.1.360
		hsw3000c01v3In2WssCodTrapEnable OBJECT-TYPE
			SYNTAX AlarmEnable
			MAX-ACCESS read-write
			STATUS current
			DESCRIPTION
				"WSS group 1 data  (b3-b0) Trap Enable"
		::= { hsw3000c01v3Entry 360 }

		-- 1.3.6.1.4.1.10106.3.101291.1.1.361
		hsw3000c01v3In2ViiAfdCod OBJECT-TYPE
			SYNTAX Code4Bit
			MAX-ACCESS read-only
			STATUS current
			DESCRIPTION
				"VII AFD code (a3-a0)"
		::= { hsw3000c01v3Entry 361 }

		-- 1.3.6.1.4.1.10106.3.101291.1.1.362
		hsw3000c01v3In2ViiAfdCodTrapEnable OBJECT-TYPE
			SYNTAX AlarmEnable
			MAX-ACCESS read-write
			STATUS current
			DESCRIPTION
				"VII AFD code (a3-a0) Trap Enable"
		::= { hsw3000c01v3Entry 362 }

		-- 1.3.6.1.4.1.10106.3.101291.1.1.363
		hsw3000c01v3In22016Cod OBJECT-TYPE
			SYNTAX Code4Bit
			MAX-ACCESS read-only
			STATUS current
			DESCRIPTION
				"SMPTE 2016 AFD code (a3-a0)"
		::= { hsw3000c01v3Entry 363 }

		-- 1.3.6.1.4.1.10106.3.101291.1.1.364
		hsw3000c01v3In22016CodTrapEnable OBJECT-TYPE
			SYNTAX AlarmEnable
			MAX-ACCESS read-write
			STATUS current
			DESCRIPTION
				"SMPTE 2016 AFD code (a3-a0) Trap Enable"
		::= { hsw3000c01v3Entry 364 }

		-- 1.3.6.1.4.1.10106.3.371701
		eop0020c01v1 OBJECT IDENTIFIER ::= { albalaProducts 371701 }

		-- 1.3.6.1.4.1.10106.3.371701.1
		eop0020c01v1Table  OBJECT-TYPE
			SYNTAX SEQUENCE OF Eop0020c01v1Entry
			MAX-ACCESS not-accessible
			STATUS current
			DESCRIPTION
				"Module  EOP0020C01V1 Table"
			::= { eop0020c01v1 1 }

		-- 1.3.6.1.4.1.10106.3.371701.1.1
		eop0020c01v1Entry  OBJECT-TYPE
			SYNTAX Eop0020c01v1Entry
			MAX-ACCESS not-accessible
			STATUS current
			DESCRIPTION
				"Module EOP0020C01V1 Entry"
			INDEX { eop0020c01v1Index }
			::= { eop0020c01v1Table 1 }

			Eop0020c01v1Entry ::=
			SEQUENCE {
				eop0020c01v1Index
				ModuleIndex,
				eop0020c01v1ForceAdjacent
				Bit0No1Yes,
				eop0020c01v1NoSigA
				BitFail,
				eop0020c01v1NoSigATrapEnable
				AlarmEnable,
				eop0020c01v1UnlockA
				BitFail,
				eop0020c01v1UnlockATrapEnable
				AlarmEnable,
				eop0020c01v1LFailA
				BitFail,
				eop0020c01v1LFailATrapEnable
				AlarmEnable,
				eop0020c01v1NoSigB
				BitFail,
				eop0020c01v1NoSigBTrapEnable
				AlarmEnable,
				eop0020c01v1UnlockB
				BitFail,
				eop0020c01v1UnlockBTrapEnable
				AlarmEnable,
				eop0020c01v1LFailB
				BitFail,
				eop0020c01v1LFailBTrapEnable
				AlarmEnable,
				eop0020c01v1SfpId
				SfpType,
				eop0020c01v1SfpSn
				SerialNo,
				eop0020c01v1Temperature
				Temperature0c1,
				eop0020c01v1RxPowerA
				OptPowerX2Uw,
				eop0020c01v1RxPowerB
				OptPowerX2Uw
			 }

		-- 1.3.6.1.4.1.10106.3.101291.1.1.1
		eop0020c01v1Index OBJECT-TYPE
			SYNTAX ModuleIndex
			MAX-ACCESS read-only
			STATUS current
			DESCRIPTION
				"Index of EOP0020C01V1 Table"
		::= { eop0020c01v1Entry 1 }

		-- 1.3.6.1.4.1.10106.3.101291.1.1.3
		eop0020c01v1ForceAdjacent OBJECT-TYPE
			SYNTAX Bit0No1Yes
			MAX-ACCESS read-write
			STATUS current
			DESCRIPTION
				"Inputs from adjacent section"
		::= { eop0020c01v1Entry 3 }

		-- 1.3.6.1.4.1.10106.3.101291.1.1.5
		eop0020c01v1NoSigA OBJECT-TYPE
			SYNTAX BitFail
			MAX-ACCESS read-only
			STATUS current
			DESCRIPTION
				"Input signal status"
		::= { eop0020c01v1Entry 5 }

		-- 1.3.6.1.4.1.10106.3.101291.1.1.6
		eop0020c01v1NoSigATrapEnable OBJECT-TYPE
			SYNTAX AlarmEnable
			MAX-ACCESS read-write
			STATUS current
			DESCRIPTION
				"Input signal status Trap Enable"
		::= { eop0020c01v1Entry 6 }

		-- 1.3.6.1.4.1.10106.3.101291.1.1.7
		eop0020c01v1UnlockA OBJECT-TYPE
			SYNTAX BitFail
			MAX-ACCESS read-only
			STATUS current
			DESCRIPTION
				"Indicates signal unlock fail"
		::= { eop0020c01v1Entry 7 }

		-- 1.3.6.1.4.1.10106.3.101291.1.1.8
		eop0020c01v1UnlockATrapEnable OBJECT-TYPE
			SYNTAX AlarmEnable
			MAX-ACCESS read-write
			STATUS current
			DESCRIPTION
				"Indicates signal unlock fail Trap Enable"
		::= { eop0020c01v1Entry 8 }

		-- 1.3.6.1.4.1.10106.3.101291.1.1.9
		eop0020c01v1LFailA OBJECT-TYPE
			SYNTAX BitFail
			MAX-ACCESS read-only
			STATUS current
			DESCRIPTION
				"Indicates a fail in laser"
		::= { eop0020c01v1Entry 9 }

		-- 1.3.6.1.4.1.10106.3.101291.1.1.10
		eop0020c01v1LFailATrapEnable OBJECT-TYPE
			SYNTAX AlarmEnable
			MAX-ACCESS read-write
			STATUS current
			DESCRIPTION
				"Indicates a fail in laser Trap Enable"
		::= { eop0020c01v1Entry 10 }

		-- 1.3.6.1.4.1.10106.3.101291.1.1.11
		eop0020c01v1NoSigB OBJECT-TYPE
			SYNTAX BitFail
			MAX-ACCESS read-only
			STATUS current
			DESCRIPTION
				"Input signal status"
		::= { eop0020c01v1Entry 11 }

		-- 1.3.6.1.4.1.10106.3.101291.1.1.12
		eop0020c01v1NoSigBTrapEnable OBJECT-TYPE
			SYNTAX AlarmEnable
			MAX-ACCESS read-write
			STATUS current
			DESCRIPTION
				"Input signal status Trap Enable"
		::= { eop0020c01v1Entry 12 }

		-- 1.3.6.1.4.1.10106.3.101291.1.1.13
		eop0020c01v1UnlockB OBJECT-TYPE
			SYNTAX BitFail
			MAX-ACCESS read-only
			STATUS current
			DESCRIPTION
				"Indicates signal unlock fail"
		::= { eop0020c01v1Entry 13 }

		-- 1.3.6.1.4.1.10106.3.101291.1.1.14
		eop0020c01v1UnlockBTrapEnable OBJECT-TYPE
			SYNTAX AlarmEnable
			MAX-ACCESS read-write
			STATUS current
			DESCRIPTION
				"Indicates signal unlock fail Trap Enable"
		::= { eop0020c01v1Entry 14 }

		-- 1.3.6.1.4.1.10106.3.101291.1.1.15
		eop0020c01v1LFailB OBJECT-TYPE
			SYNTAX BitFail
			MAX-ACCESS read-only
			STATUS current
			DESCRIPTION
				"Indicates a fail in laser"
		::= { eop0020c01v1Entry 15 }

		-- 1.3.6.1.4.1.10106.3.101291.1.1.16
		eop0020c01v1LFailBTrapEnable OBJECT-TYPE
			SYNTAX AlarmEnable
			MAX-ACCESS read-write
			STATUS current
			DESCRIPTION
				"Indicates a fail in laser Trap Enable"
		::= { eop0020c01v1Entry 16 }

		-- 1.3.6.1.4.1.10106.3.101291.1.1.17
		eop0020c01v1SfpId OBJECT-TYPE
			SYNTAX SfpType
			MAX-ACCESS read-only
			STATUS current
			DESCRIPTION
				"Indicates the presence of a SFP module"
		::= { eop0020c01v1Entry 17 }

		-- 1.3.6.1.4.1.10106.3.101291.1.1.19
		eop0020c01v1SfpSn OBJECT-TYPE
			SYNTAX SerialNo
			MAX-ACCESS read-only
			STATUS current
			DESCRIPTION
				"SFP Serial number"
		::= { eop0020c01v1Entry 19 }

		-- 1.3.6.1.4.1.10106.3.101291.1.1.21
		eop0020c01v1Temperature OBJECT-TYPE
			SYNTAX Temperature0c1
			MAX-ACCESS read-only
			STATUS current
			DESCRIPTION
				"SFP module temperatura"
		::= { eop0020c01v1Entry 21 }

		-- 1.3.6.1.4.1.10106.3.101291.1.1.23
		eop0020c01v1RxPowerA OBJECT-TYPE
			SYNTAX OptPowerX2Uw
			MAX-ACCESS read-only
			STATUS current
			DESCRIPTION
				"Optical received power"
		::= { eop0020c01v1Entry 23 }

		-- 1.3.6.1.4.1.10106.3.101291.1.1.25
		eop0020c01v1RxPowerB OBJECT-TYPE
			SYNTAX OptPowerX2Uw
			MAX-ACCESS read-only
			STATUS current
			DESCRIPTION
				"Optical received power"
		::= { eop0020c01v1Entry 25 }

		-- 1.3.6.1.4.1.10106.3.373501
		hop3147c01v1 OBJECT IDENTIFIER ::= { albalaProducts 373501 }

		-- 1.3.6.1.4.1.10106.3.373501.1
		hop3147c01v1Table  OBJECT-TYPE
			SYNTAX SEQUENCE OF Hop3147c01v1Entry
			MAX-ACCESS not-accessible
			STATUS current
			DESCRIPTION
				"Module  HOP3147C01V1 Table"
			::= { hop3147c01v1 1 }

		-- 1.3.6.1.4.1.10106.3.373501.1.1
		hop3147c01v1Entry  OBJECT-TYPE
			SYNTAX Hop3147c01v1Entry
			MAX-ACCESS not-accessible
			STATUS current
			DESCRIPTION
				"Module HOP3147C01V1 Entry"
			INDEX { hop3147c01v1Index }
			::= { hop3147c01v1Table 1 }

			Hop3147c01v1Entry ::=
			SEQUENCE {
				hop3147c01v1Index
				ModuleIndex,
				hop3147c01v1TxtInsEna1
				BitMask,
				hop3147c01v1TxtInsEna2
				BitMask,
				hop3147c01v1Op47InsEna
				BitMask,
				hop3147c01v1TxtCleanEna1
				BitMask,
				hop3147c01v1TxtCleanEna2
				BitMask,
				hop3147c01v1Op47CleanEna
				BitMask,
				hop3147c01v1LumChromN
				Bit0Chr1Lum,
				hop3147c01v1Gpo8SigFail
				Bit0No1Yes,
				hop3147c01v1Op47PckInsLin
				Uint5,
				hop3147c01v1TxtInsLine1
				Uint5,
				hop3147c01v1TxtInsLine2
				Uint5,
				hop3147c01v1TxtRdLine
				Uint5,
				hop3147c01v1TxtRdEna
				BitMask,
				hop3147c01v1NoSignal
				BitFail,
				hop3147c01v1NoSignalTrapEnable
				AlarmEnable,
				hop3147c01v1Unlock
				BitFail,
				hop3147c01v1UnlockTrapEnable
				AlarmEnable,
				hop3147c01v1EdhError
				BitFail,
				hop3147c01v1EdhErrorTrapEnable
				AlarmEnable,
				hop3147c01v1TxtFail
				BitFail,
				hop3147c01v1TxtFailTrapEnable
				AlarmEnable,
				hop3147c01v1TxtInsFail
				BitFail,
				hop3147c01v1TxtInsFailTrapEnable
				AlarmEnable,
				hop3147c01v1Format
				SdiHd3gFmt3,
				hop3147c01v1Gpi1
				Bit0Off1On,
				hop3147c01v1Gpi1TrapEnable
				AlarmEnable,
				hop3147c01v1Gpi2
				Bit0Off1On,
				hop3147c01v1Gpi2TrapEnable
				AlarmEnable,
				hop3147c01v1Gpi3
				Bit0Off1On,
				hop3147c01v1Gpi3TrapEnable
				AlarmEnable,
				hop3147c01v1Gpi4
				Bit0Off1On,
				hop3147c01v1Gpi4TrapEnable
				AlarmEnable,
				hop3147c01v1Gpi5
				Bit0Off1On,
				hop3147c01v1Gpi5TrapEnable
				AlarmEnable,
				hop3147c01v1Gpi6
				Bit0Off1On,
				hop3147c01v1Gpi6TrapEnable
				AlarmEnable,
				hop3147c01v1Gpi7
				Bit0Off1On,
				hop3147c01v1Gpi7TrapEnable
				AlarmEnable,
				hop3147c01v1Gpi8
				Bit0Off1On,
				hop3147c01v1Gpi8TrapEnable
				AlarmEnable,
				hop3147c01v1Gpo1
				Bit0Off1On,
				hop3147c01v1Gpo1TrapEnable
				AlarmEnable,
				hop3147c01v1Gpo2
				Bit0Off1On,
				hop3147c01v1Gpo2TrapEnable
				AlarmEnable,
				hop3147c01v1Gpo3
				Bit0Off1On,
				hop3147c01v1Gpo3TrapEnable
				AlarmEnable,
				hop3147c01v1Gpo4
				Bit0Off1On,
				hop3147c01v1Gpo4TrapEnable
				AlarmEnable,
				hop3147c01v1Gpo5
				Bit0Off1On,
				hop3147c01v1Gpo5TrapEnable
				AlarmEnable,
				hop3147c01v1Gpo6
				Bit0Off1On,
				hop3147c01v1Gpo6TrapEnable
				AlarmEnable,
				hop3147c01v1Gpo7
				Bit0Off1On,
				hop3147c01v1Gpo7TrapEnable
				AlarmEnable,
				hop3147c01v1Gpo8
				Bit0Off1On,
				hop3147c01v1Gpo8TrapEnable
				AlarmEnable,
				hop3147c01v1SerialNo
				SerialNo
			 }

		-- 1.3.6.1.4.1.10106.3.101291.1.1.1
		hop3147c01v1Index OBJECT-TYPE
			SYNTAX ModuleIndex
			MAX-ACCESS read-only
			STATUS current
			DESCRIPTION
				"Index of HOP3147C01V1 Table"
		::= { hop3147c01v1Entry 1 }

		-- 1.3.6.1.4.1.10106.3.101291.1.1.3
		hop3147c01v1TxtInsEna1 OBJECT-TYPE
			SYNTAX BitMask
			MAX-ACCESS read-write
			STATUS current
			DESCRIPTION
				"Enables insertion in SD_L1"
		::= { hop3147c01v1Entry 3 }

		-- 1.3.6.1.4.1.10106.3.101291.1.1.5
		hop3147c01v1TxtInsEna2 OBJECT-TYPE
			SYNTAX BitMask
			MAX-ACCESS read-write
			STATUS current
			DESCRIPTION
				"Enables insertion in SD_L2"
		::= { hop3147c01v1Entry 5 }

		-- 1.3.6.1.4.1.10106.3.101291.1.1.7
		hop3147c01v1Op47InsEna OBJECT-TYPE
			SYNTAX BitMask
			MAX-ACCESS read-write
			STATUS current
			DESCRIPTION
				"Enables insertion in HD"
		::= { hop3147c01v1Entry 7 }

		-- 1.3.6.1.4.1.10106.3.101291.1.1.9
		hop3147c01v1TxtCleanEna1 OBJECT-TYPE
			SYNTAX BitMask
			MAX-ACCESS read-write
			STATUS current
			DESCRIPTION
				"Enables cleaning active part of a line to remove teletext data"
		::= { hop3147c01v1Entry 9 }

		-- 1.3.6.1.4.1.10106.3.101291.1.1.11
		hop3147c01v1TxtCleanEna2 OBJECT-TYPE
			SYNTAX BitMask
			MAX-ACCESS read-write
			STATUS current
			DESCRIPTION
				"Enables cleaning active part of a line to remove teletext data"
		::= { hop3147c01v1Entry 11 }

		-- 1.3.6.1.4.1.10106.3.101291.1.1.13
		hop3147c01v1Op47CleanEna OBJECT-TYPE
			SYNTAX BitMask
			MAX-ACCESS read-write
			STATUS current
			DESCRIPTION
				"Enables cleaning active part of a line to remove OP47"
		::= { hop3147c01v1Entry 13 }

		-- 1.3.6.1.4.1.10106.3.101291.1.1.15
		hop3147c01v1LumChromN OBJECT-TYPE
			SYNTAX Bit0Chr1Lum
			MAX-ACCESS read-write
			STATUS current
			DESCRIPTION
				"Allows selecting if the OP47 packet is inserted in luminance or in chrominace"
		::= { hop3147c01v1Entry 15 }

		-- 1.3.6.1.4.1.10106.3.101291.1.1.17
		hop3147c01v1Gpo8SigFail OBJECT-TYPE
			SYNTAX Bit0No1Yes
			MAX-ACCESS read-write
			STATUS current
			DESCRIPTION
				"GPO8 used to signal fail"
		::= { hop3147c01v1Entry 17 }

		-- 1.3.6.1.4.1.10106.3.101291.1.1.19
		hop3147c01v1Op47PckInsLin OBJECT-TYPE
			SYNTAX Uint5
			MAX-ACCESS read-write
			STATUS current
			DESCRIPTION
				"HD insertion line (OP47 packet)"
		::= { hop3147c01v1Entry 19 }

		-- 1.3.6.1.4.1.10106.3.101291.1.1.21
		hop3147c01v1TxtInsLine1 OBJECT-TYPE
			SYNTAX Uint5
			MAX-ACCESS read-write
			STATUS current
			DESCRIPTION
				"SD_L1 insertion line (Teletext A)"
		::= { hop3147c01v1Entry 21 }

		-- 1.3.6.1.4.1.10106.3.101291.1.1.23
		hop3147c01v1TxtInsLine2 OBJECT-TYPE
			SYNTAX Uint5
			MAX-ACCESS read-write
			STATUS current
			DESCRIPTION
				"SD_L2 insertion line (Teletext B)"
		::= { hop3147c01v1Entry 23 }

		-- 1.3.6.1.4.1.10106.3.101291.1.1.25
		hop3147c01v1TxtRdLine OBJECT-TYPE
			SYNTAX Uint5
			MAX-ACCESS read-write
			STATUS current
			DESCRIPTION
				"Teletext read line"
		::= { hop3147c01v1Entry 25 }

		-- 1.3.6.1.4.1.10106.3.101291.1.1.27
		hop3147c01v1TxtRdEna OBJECT-TYPE
			SYNTAX BitMask
			MAX-ACCESS read-write
			STATUS current
			DESCRIPTION
				"Enables reading Teletext"
		::= { hop3147c01v1Entry 27 }

		-- 1.3.6.1.4.1.10106.3.101291.1.1.29
		hop3147c01v1NoSignal OBJECT-TYPE
			SYNTAX BitFail
			MAX-ACCESS read-only
			STATUS current
			DESCRIPTION
				"There is no SDI signal or the format is not supported"
		::= { hop3147c01v1Entry 29 }

		-- 1.3.6.1.4.1.10106.3.101291.1.1.30
		hop3147c01v1NoSignalTrapEnable OBJECT-TYPE
			SYNTAX AlarmEnable
			MAX-ACCESS read-write
			STATUS current
			DESCRIPTION
				"There is no SDI signal or the format is not supported Trap Enable"
		::= { hop3147c01v1Entry 30 }

		-- 1.3.6.1.4.1.10106.3.101291.1.1.31
		hop3147c01v1Unlock OBJECT-TYPE
			SYNTAX BitFail
			MAX-ACCESS read-only
			STATUS current
			DESCRIPTION
				"Indicates signal unlock fail"
		::= { hop3147c01v1Entry 31 }

		-- 1.3.6.1.4.1.10106.3.101291.1.1.32
		hop3147c01v1UnlockTrapEnable OBJECT-TYPE
			SYNTAX AlarmEnable
			MAX-ACCESS read-write
			STATUS current
			DESCRIPTION
				"Indicates signal unlock fail Trap Enable"
		::= { hop3147c01v1Entry 32 }

		-- 1.3.6.1.4.1.10106.3.101291.1.1.33
		hop3147c01v1EdhError OBJECT-TYPE
			SYNTAX BitFail
			MAX-ACCESS read-only
			STATUS current
			DESCRIPTION
				"There are EDH/CRC errors on SDI signal"
		::= { hop3147c01v1Entry 33 }

		-- 1.3.6.1.4.1.10106.3.101291.1.1.34
		hop3147c01v1EdhErrorTrapEnable OBJECT-TYPE
			SYNTAX AlarmEnable
			MAX-ACCESS read-write
			STATUS current
			DESCRIPTION
				"There are EDH/CRC errors on SDI signal Trap Enable"
		::= { hop3147c01v1Entry 34 }

		-- 1.3.6.1.4.1.10106.3.101291.1.1.35
		hop3147c01v1TxtFail OBJECT-TYPE
			SYNTAX BitFail
			MAX-ACCESS read-only
			STATUS current
			DESCRIPTION
				"Teletext signal not found"
		::= { hop3147c01v1Entry 35 }

		-- 1.3.6.1.4.1.10106.3.101291.1.1.36
		hop3147c01v1TxtFailTrapEnable OBJECT-TYPE
			SYNTAX AlarmEnable
			MAX-ACCESS read-write
			STATUS current
			DESCRIPTION
				"Teletext signal not found Trap Enable"
		::= { hop3147c01v1Entry 36 }

		-- 1.3.6.1.4.1.10106.3.101291.1.1.37
		hop3147c01v1TxtInsFail OBJECT-TYPE
			SYNTAX BitFail
			MAX-ACCESS read-only
			STATUS current
			DESCRIPTION
				"OP47 packet can not be insertedl"
		::= { hop3147c01v1Entry 37 }

		-- 1.3.6.1.4.1.10106.3.101291.1.1.38
		hop3147c01v1TxtInsFailTrapEnable OBJECT-TYPE
			SYNTAX AlarmEnable
			MAX-ACCESS read-write
			STATUS current
			DESCRIPTION
				"OP47 packet can not be insertedl Trap Enable"
		::= { hop3147c01v1Entry 38 }

		-- 1.3.6.1.4.1.10106.3.101291.1.1.39
		hop3147c01v1Format OBJECT-TYPE
			SYNTAX SdiHd3gFmt3
			MAX-ACCESS read-only
			STATUS current
			DESCRIPTION
				"Indicates the SDI received signal format"
		::= { hop3147c01v1Entry 39 }

		-- 1.3.6.1.4.1.10106.3.101291.1.1.41
		hop3147c01v1Gpi1 OBJECT-TYPE
			SYNTAX Bit0Off1On
			MAX-ACCESS read-only
			STATUS current
			DESCRIPTION
				"Transmitted GPI1"
		::= { hop3147c01v1Entry 41 }

		-- 1.3.6.1.4.1.10106.3.101291.1.1.42
		hop3147c01v1Gpi1TrapEnable OBJECT-TYPE
			SYNTAX AlarmEnable
			MAX-ACCESS read-write
			STATUS current
			DESCRIPTION
				"Transmitted GPI1 Trap Enable"
		::= { hop3147c01v1Entry 42 }

		-- 1.3.6.1.4.1.10106.3.101291.1.1.43
		hop3147c01v1Gpi2 OBJECT-TYPE
			SYNTAX Bit0Off1On
			MAX-ACCESS read-only
			STATUS current
			DESCRIPTION
				"Transmitted GPI2"
		::= { hop3147c01v1Entry 43 }

		-- 1.3.6.1.4.1.10106.3.101291.1.1.44
		hop3147c01v1Gpi2TrapEnable OBJECT-TYPE
			SYNTAX AlarmEnable
			MAX-ACCESS read-write
			STATUS current
			DESCRIPTION
				"Transmitted GPI2 Trap Enable"
		::= { hop3147c01v1Entry 44 }

		-- 1.3.6.1.4.1.10106.3.101291.1.1.45
		hop3147c01v1Gpi3 OBJECT-TYPE
			SYNTAX Bit0Off1On
			MAX-ACCESS read-only
			STATUS current
			DESCRIPTION
				"Transmitted GPI3"
		::= { hop3147c01v1Entry 45 }

		-- 1.3.6.1.4.1.10106.3.101291.1.1.46
		hop3147c01v1Gpi3TrapEnable OBJECT-TYPE
			SYNTAX AlarmEnable
			MAX-ACCESS read-write
			STATUS current
			DESCRIPTION
				"Transmitted GPI3 Trap Enable"
		::= { hop3147c01v1Entry 46 }

		-- 1.3.6.1.4.1.10106.3.101291.1.1.47
		hop3147c01v1Gpi4 OBJECT-TYPE
			SYNTAX Bit0Off1On
			MAX-ACCESS read-only
			STATUS current
			DESCRIPTION
				"Transmitted GPI4"
		::= { hop3147c01v1Entry 47 }

		-- 1.3.6.1.4.1.10106.3.101291.1.1.48
		hop3147c01v1Gpi4TrapEnable OBJECT-TYPE
			SYNTAX AlarmEnable
			MAX-ACCESS read-write
			STATUS current
			DESCRIPTION
				"Transmitted GPI4 Trap Enable"
		::= { hop3147c01v1Entry 48 }

		-- 1.3.6.1.4.1.10106.3.101291.1.1.49
		hop3147c01v1Gpi5 OBJECT-TYPE
			SYNTAX Bit0Off1On
			MAX-ACCESS read-only
			STATUS current
			DESCRIPTION
				"Transmitted GPI5"
		::= { hop3147c01v1Entry 49 }

		-- 1.3.6.1.4.1.10106.3.101291.1.1.50
		hop3147c01v1Gpi5TrapEnable OBJECT-TYPE
			SYNTAX AlarmEnable
			MAX-ACCESS read-write
			STATUS current
			DESCRIPTION
				"Transmitted GPI5 Trap Enable"
		::= { hop3147c01v1Entry 50 }

		-- 1.3.6.1.4.1.10106.3.101291.1.1.51
		hop3147c01v1Gpi6 OBJECT-TYPE
			SYNTAX Bit0Off1On
			MAX-ACCESS read-only
			STATUS current
			DESCRIPTION
				"Transmitted GPI6"
		::= { hop3147c01v1Entry 51 }

		-- 1.3.6.1.4.1.10106.3.101291.1.1.52
		hop3147c01v1Gpi6TrapEnable OBJECT-TYPE
			SYNTAX AlarmEnable
			MAX-ACCESS read-write
			STATUS current
			DESCRIPTION
				"Transmitted GPI6 Trap Enable"
		::= { hop3147c01v1Entry 52 }

		-- 1.3.6.1.4.1.10106.3.101291.1.1.53
		hop3147c01v1Gpi7 OBJECT-TYPE
			SYNTAX Bit0Off1On
			MAX-ACCESS read-only
			STATUS current
			DESCRIPTION
				"Transmitted GPI7"
		::= { hop3147c01v1Entry 53 }

		-- 1.3.6.1.4.1.10106.3.101291.1.1.54
		hop3147c01v1Gpi7TrapEnable OBJECT-TYPE
			SYNTAX AlarmEnable
			MAX-ACCESS read-write
			STATUS current
			DESCRIPTION
				"Transmitted GPI7 Trap Enable"
		::= { hop3147c01v1Entry 54 }

		-- 1.3.6.1.4.1.10106.3.101291.1.1.55
		hop3147c01v1Gpi8 OBJECT-TYPE
			SYNTAX Bit0Off1On
			MAX-ACCESS read-only
			STATUS current
			DESCRIPTION
				"Transmitted GPI8"
		::= { hop3147c01v1Entry 55 }

		-- 1.3.6.1.4.1.10106.3.101291.1.1.56
		hop3147c01v1Gpi8TrapEnable OBJECT-TYPE
			SYNTAX AlarmEnable
			MAX-ACCESS read-write
			STATUS current
			DESCRIPTION
				"Transmitted GPI8 Trap Enable"
		::= { hop3147c01v1Entry 56 }

		-- 1.3.6.1.4.1.10106.3.101291.1.1.57
		hop3147c01v1Gpo1 OBJECT-TYPE
			SYNTAX Bit0Off1On
			MAX-ACCESS read-only
			STATUS current
			DESCRIPTION
				"Received GPO1"
		::= { hop3147c01v1Entry 57 }

		-- 1.3.6.1.4.1.10106.3.101291.1.1.58
		hop3147c01v1Gpo1TrapEnable OBJECT-TYPE
			SYNTAX AlarmEnable
			MAX-ACCESS read-write
			STATUS current
			DESCRIPTION
				"Received GPO1 Trap Enable"
		::= { hop3147c01v1Entry 58 }

		-- 1.3.6.1.4.1.10106.3.101291.1.1.59
		hop3147c01v1Gpo2 OBJECT-TYPE
			SYNTAX Bit0Off1On
			MAX-ACCESS read-only
			STATUS current
			DESCRIPTION
				"Received GPO2"
		::= { hop3147c01v1Entry 59 }

		-- 1.3.6.1.4.1.10106.3.101291.1.1.60
		hop3147c01v1Gpo2TrapEnable OBJECT-TYPE
			SYNTAX AlarmEnable
			MAX-ACCESS read-write
			STATUS current
			DESCRIPTION
				"Received GPO2 Trap Enable"
		::= { hop3147c01v1Entry 60 }

		-- 1.3.6.1.4.1.10106.3.101291.1.1.61
		hop3147c01v1Gpo3 OBJECT-TYPE
			SYNTAX Bit0Off1On
			MAX-ACCESS read-only
			STATUS current
			DESCRIPTION
				"Received GPO3"
		::= { hop3147c01v1Entry 61 }

		-- 1.3.6.1.4.1.10106.3.101291.1.1.62
		hop3147c01v1Gpo3TrapEnable OBJECT-TYPE
			SYNTAX AlarmEnable
			MAX-ACCESS read-write
			STATUS current
			DESCRIPTION
				"Received GPO3 Trap Enable"
		::= { hop3147c01v1Entry 62 }

		-- 1.3.6.1.4.1.10106.3.101291.1.1.63
		hop3147c01v1Gpo4 OBJECT-TYPE
			SYNTAX Bit0Off1On
			MAX-ACCESS read-only
			STATUS current
			DESCRIPTION
				"Received GPO4"
		::= { hop3147c01v1Entry 63 }

		-- 1.3.6.1.4.1.10106.3.101291.1.1.64
		hop3147c01v1Gpo4TrapEnable OBJECT-TYPE
			SYNTAX AlarmEnable
			MAX-ACCESS read-write
			STATUS current
			DESCRIPTION
				"Received GPO4 Trap Enable"
		::= { hop3147c01v1Entry 64 }

		-- 1.3.6.1.4.1.10106.3.101291.1.1.65
		hop3147c01v1Gpo5 OBJECT-TYPE
			SYNTAX Bit0Off1On
			MAX-ACCESS read-only
			STATUS current
			DESCRIPTION
				"Received GPO5"
		::= { hop3147c01v1Entry 65 }

		-- 1.3.6.1.4.1.10106.3.101291.1.1.66
		hop3147c01v1Gpo5TrapEnable OBJECT-TYPE
			SYNTAX AlarmEnable
			MAX-ACCESS read-write
			STATUS current
			DESCRIPTION
				"Received GPO5 Trap Enable"
		::= { hop3147c01v1Entry 66 }

		-- 1.3.6.1.4.1.10106.3.101291.1.1.67
		hop3147c01v1Gpo6 OBJECT-TYPE
			SYNTAX Bit0Off1On
			MAX-ACCESS read-only
			STATUS current
			DESCRIPTION
				"Received GPO6"
		::= { hop3147c01v1Entry 67 }

		-- 1.3.6.1.4.1.10106.3.101291.1.1.68
		hop3147c01v1Gpo6TrapEnable OBJECT-TYPE
			SYNTAX AlarmEnable
			MAX-ACCESS read-write
			STATUS current
			DESCRIPTION
				"Received GPO6 Trap Enable"
		::= { hop3147c01v1Entry 68 }

		-- 1.3.6.1.4.1.10106.3.101291.1.1.69
		hop3147c01v1Gpo7 OBJECT-TYPE
			SYNTAX Bit0Off1On
			MAX-ACCESS read-only
			STATUS current
			DESCRIPTION
				"Received GPO7"
		::= { hop3147c01v1Entry 69 }

		-- 1.3.6.1.4.1.10106.3.101291.1.1.70
		hop3147c01v1Gpo7TrapEnable OBJECT-TYPE
			SYNTAX AlarmEnable
			MAX-ACCESS read-write
			STATUS current
			DESCRIPTION
				"Received GPO7 Trap Enable"
		::= { hop3147c01v1Entry 70 }

		-- 1.3.6.1.4.1.10106.3.101291.1.1.71
		hop3147c01v1Gpo8 OBJECT-TYPE
			SYNTAX Bit0Off1On
			MAX-ACCESS read-only
			STATUS current
			DESCRIPTION
				"Received GPO8"
		::= { hop3147c01v1Entry 71 }

		-- 1.3.6.1.4.1.10106.3.101291.1.1.72
		hop3147c01v1Gpo8TrapEnable OBJECT-TYPE
			SYNTAX AlarmEnable
			MAX-ACCESS read-write
			STATUS current
			DESCRIPTION
				"Received GPO8 Trap Enable"
		::= { hop3147c01v1Entry 72 }

		-- 1.3.6.1.4.1.10106.3.101291.1.1.73
		hop3147c01v1SerialNo OBJECT-TYPE
			SYNTAX SerialNo
			MAX-ACCESS read-only
			STATUS current
			DESCRIPTION
				"Serial number"
		::= { hop3147c01v1Entry 73 }

		-- 1.3.6.1.4.1.10106.3.375001
		hvp3000c01v1 OBJECT IDENTIFIER ::= { albalaProducts 375001 }

		-- 1.3.6.1.4.1.10106.3.375001.1
		hvp3000c01v1Table  OBJECT-TYPE
			SYNTAX SEQUENCE OF Hvp3000c01v1Entry
			MAX-ACCESS not-accessible
			STATUS current
			DESCRIPTION
				"Module  HVP3000C01V1 Table"
			::= { hvp3000c01v1 1 }

		-- 1.3.6.1.4.1.10106.3.375001.1.1
		hvp3000c01v1Entry  OBJECT-TYPE
			SYNTAX Hvp3000c01v1Entry
			MAX-ACCESS not-accessible
			STATUS current
			DESCRIPTION
				"Module HVP3000C01V1 Entry"
			INDEX { hvp3000c01v1Index }
			::= { hvp3000c01v1Table 1 }

			Hvp3000c01v1Entry ::=
			SEQUENCE {
				hvp3000c01v1Index
				ModuleIndex,
				hvp3000c01v1Output1
				Gpos0255,
				hvp3000c01v1Output1TrapEnable
				AlarmEnable,
				hvp3000c01v1Output2
				Gpos0255,
				hvp3000c01v1Output2TrapEnable
				AlarmEnable,
				hvp3000c01v1Output3
				Gpos0255,
				hvp3000c01v1Output3TrapEnable
				AlarmEnable,
				hvp3000c01v1Output4
				Gpos0255,
				hvp3000c01v1Output4TrapEnable
				AlarmEnable,
				hvp3000c01v1SwitchTime
				PreselSwTime3,
				hvp3000c01v1HvpMode
				HvpMode,
				hvp3000c01v1CasdadeMode
				Bit0No1Yes,
				hvp3000c01v1SwitchMode
				PreselSwMode1,
				hvp3000c01v1InputOffset
				Uint6,
				hvp3000c01v1SyncFormat
				SdiHd3gFmt4,
				hvp3000c01v1SyncFormatTrapEnable
				AlarmEnable,
				hvp3000c01v1Out1LckStat
				HvpLockStatus,
				hvp3000c01v1Out1LckStatTrapEnable
				AlarmEnable,
				hvp3000c01v1Out2LckStat
				HvpLockStatus,
				hvp3000c01v1Out2LckStatTrapEnable
				AlarmEnable,
				hvp3000c01v1Out3LckStat
				HvpLockStatus,
				hvp3000c01v1Out3LckStatTrapEnable
				AlarmEnable,
				hvp3000c01v1Out4LckStat
				HvpLockStatus,
				hvp3000c01v1Out4LckStatTrapEnable
				AlarmEnable,
				hvp3000c01v1SerialNo
				SerialNo
			 }

		-- 1.3.6.1.4.1.10106.3.101291.1.1.1
		hvp3000c01v1Index OBJECT-TYPE
			SYNTAX ModuleIndex
			MAX-ACCESS read-only
			STATUS current
			DESCRIPTION
				"Index of HVP3000C01V1 Table"
		::= { hvp3000c01v1Entry 1 }

		-- 1.3.6.1.4.1.10106.3.101291.1.1.3
		hvp3000c01v1Output1 OBJECT-TYPE
			SYNTAX Gpos0255
			MAX-ACCESS read-write
			STATUS current
			DESCRIPTION
				"Input routed to output 1"
		::= { hvp3000c01v1Entry 3 }

		-- 1.3.6.1.4.1.10106.3.101291.1.1.4
		hvp3000c01v1Output1TrapEnable OBJECT-TYPE
			SYNTAX AlarmEnable
			MAX-ACCESS read-write
			STATUS current
			DESCRIPTION
				"Input routed to output 1 Trap Enable"
		::= { hvp3000c01v1Entry 4 }

		-- 1.3.6.1.4.1.10106.3.101291.1.1.5
		hvp3000c01v1Output2 OBJECT-TYPE
			SYNTAX Gpos0255
			MAX-ACCESS read-write
			STATUS current
			DESCRIPTION
				"Input routed to output 2"
		::= { hvp3000c01v1Entry 5 }

		-- 1.3.6.1.4.1.10106.3.101291.1.1.6
		hvp3000c01v1Output2TrapEnable OBJECT-TYPE
			SYNTAX AlarmEnable
			MAX-ACCESS read-write
			STATUS current
			DESCRIPTION
				"Input routed to output 2 Trap Enable"
		::= { hvp3000c01v1Entry 6 }

		-- 1.3.6.1.4.1.10106.3.101291.1.1.7
		hvp3000c01v1Output3 OBJECT-TYPE
			SYNTAX Gpos0255
			MAX-ACCESS read-write
			STATUS current
			DESCRIPTION
				"Input routed to output 3"
		::= { hvp3000c01v1Entry 7 }

		-- 1.3.6.1.4.1.10106.3.101291.1.1.8
		hvp3000c01v1Output3TrapEnable OBJECT-TYPE
			SYNTAX AlarmEnable
			MAX-ACCESS read-write
			STATUS current
			DESCRIPTION
				"Input routed to output 3 Trap Enable"
		::= { hvp3000c01v1Entry 8 }

		-- 1.3.6.1.4.1.10106.3.101291.1.1.9
		hvp3000c01v1Output4 OBJECT-TYPE
			SYNTAX Gpos0255
			MAX-ACCESS read-write
			STATUS current
			DESCRIPTION
				"Input routed to output 4"
		::= { hvp3000c01v1Entry 9 }

		-- 1.3.6.1.4.1.10106.3.101291.1.1.10
		hvp3000c01v1Output4TrapEnable OBJECT-TYPE
			SYNTAX AlarmEnable
			MAX-ACCESS read-write
			STATUS current
			DESCRIPTION
				"Input routed to output 4 Trap Enable"
		::= { hvp3000c01v1Entry 10 }

		-- 1.3.6.1.4.1.10106.3.101291.1.1.11
		hvp3000c01v1SwitchTime OBJECT-TYPE
			SYNTAX PreselSwTime3
			MAX-ACCESS read-write
			STATUS current
			DESCRIPTION
				"Allows selection of switching time"
		::= { hvp3000c01v1Entry 11 }

		-- 1.3.6.1.4.1.10106.3.101291.1.1.13
		hvp3000c01v1HvpMode OBJECT-TYPE
			SYNTAX HvpMode
			MAX-ACCESS read-write
			STATUS current
			DESCRIPTION
				"Allows selecting the preselector mode"
		::= { hvp3000c01v1Entry 13 }

		-- 1.3.6.1.4.1.10106.3.101291.1.1.15
		hvp3000c01v1CasdadeMode OBJECT-TYPE
			SYNTAX Bit0No1Yes
			MAX-ACCESS read-write
			STATUS current
			DESCRIPTION
				"Allows using last inputs to be connected to another preselector to expand input count"
		::= { hvp3000c01v1Entry 15 }

		-- 1.3.6.1.4.1.10106.3.101291.1.1.17
		hvp3000c01v1SwitchMode OBJECT-TYPE
			SYNTAX PreselSwMode1
			MAX-ACCESS read-write
			STATUS current
			DESCRIPTION
				"Allows selection switching mode: master or follow another module"
		::= { hvp3000c01v1Entry 17 }

		-- 1.3.6.1.4.1.10106.3.101291.1.1.19
		hvp3000c01v1InputOffset OBJECT-TYPE
			SYNTAX Uint6
			MAX-ACCESS read-write
			STATUS current
			DESCRIPTION
				"Offset between real inputs and the value that appears in registers to allow cascading switchers"
		::= { hvp3000c01v1Entry 19 }

		-- 1.3.6.1.4.1.10106.3.101291.1.1.21
		hvp3000c01v1SyncFormat OBJECT-TYPE
			SYNTAX SdiHd3gFmt4
			MAX-ACCESS read-only
			STATUS current
			DESCRIPTION
				"Displays the reference's  input format"
		::= { hvp3000c01v1Entry 21 }

		-- 1.3.6.1.4.1.10106.3.101291.1.1.22
		hvp3000c01v1SyncFormatTrapEnable OBJECT-TYPE
			SYNTAX AlarmEnable
			MAX-ACCESS read-write
			STATUS current
			DESCRIPTION
				"Displays the reference's  input format Trap Enable"
		::= { hvp3000c01v1Entry 22 }

		-- 1.3.6.1.4.1.10106.3.101291.1.1.23
		hvp3000c01v1Out1LckStat OBJECT-TYPE
			SYNTAX HvpLockStatus
			MAX-ACCESS read-only
			STATUS current
			DESCRIPTION
				"Output 1 lock status"
		::= { hvp3000c01v1Entry 23 }

		-- 1.3.6.1.4.1.10106.3.101291.1.1.24
		hvp3000c01v1Out1LckStatTrapEnable OBJECT-TYPE
			SYNTAX AlarmEnable
			MAX-ACCESS read-write
			STATUS current
			DESCRIPTION
				"Output 1 lock status Trap Enable"
		::= { hvp3000c01v1Entry 24 }

		-- 1.3.6.1.4.1.10106.3.101291.1.1.25
		hvp3000c01v1Out2LckStat OBJECT-TYPE
			SYNTAX HvpLockStatus
			MAX-ACCESS read-only
			STATUS current
			DESCRIPTION
				"Output 2 lock status"
		::= { hvp3000c01v1Entry 25 }

		-- 1.3.6.1.4.1.10106.3.101291.1.1.26
		hvp3000c01v1Out2LckStatTrapEnable OBJECT-TYPE
			SYNTAX AlarmEnable
			MAX-ACCESS read-write
			STATUS current
			DESCRIPTION
				"Output 2 lock status Trap Enable"
		::= { hvp3000c01v1Entry 26 }

		-- 1.3.6.1.4.1.10106.3.101291.1.1.27
		hvp3000c01v1Out3LckStat OBJECT-TYPE
			SYNTAX HvpLockStatus
			MAX-ACCESS read-only
			STATUS current
			DESCRIPTION
				"Output 3 lock status"
		::= { hvp3000c01v1Entry 27 }

		-- 1.3.6.1.4.1.10106.3.101291.1.1.28
		hvp3000c01v1Out3LckStatTrapEnable OBJECT-TYPE
			SYNTAX AlarmEnable
			MAX-ACCESS read-write
			STATUS current
			DESCRIPTION
				"Output 3 lock status Trap Enable"
		::= { hvp3000c01v1Entry 28 }

		-- 1.3.6.1.4.1.10106.3.101291.1.1.29
		hvp3000c01v1Out4LckStat OBJECT-TYPE
			SYNTAX HvpLockStatus
			MAX-ACCESS read-only
			STATUS current
			DESCRIPTION
				"Output 4 lock status"
		::= { hvp3000c01v1Entry 29 }

		-- 1.3.6.1.4.1.10106.3.101291.1.1.30
		hvp3000c01v1Out4LckStatTrapEnable OBJECT-TYPE
			SYNTAX AlarmEnable
			MAX-ACCESS read-write
			STATUS current
			DESCRIPTION
				"Output 4 lock status Trap Enable"
		::= { hvp3000c01v1Entry 30 }

		-- 1.3.6.1.4.1.10106.3.101291.1.1.31
		hvp3000c01v1SerialNo OBJECT-TYPE
			SYNTAX SerialNo
			MAX-ACCESS read-only
			STATUS current
			DESCRIPTION
				"Serial number"
		::= { hvp3000c01v1Entry 31 }

		-- 1.3.6.1.4.1.10106.3.376001
		tle0001c01v1 OBJECT IDENTIFIER ::= { albalaProducts 376001 }

		-- 1.3.6.1.4.1.10106.3.376001.1
		tle0001c01v1Table  OBJECT-TYPE
			SYNTAX SEQUENCE OF Tle0001c01v1Entry
			MAX-ACCESS not-accessible
			STATUS current
			DESCRIPTION
				"Module  TLE0001C01V1 Table"
			::= { tle0001c01v1 1 }

		-- 1.3.6.1.4.1.10106.3.376001.1.1
		tle0001c01v1Entry  OBJECT-TYPE
			SYNTAX Tle0001c01v1Entry
			MAX-ACCESS not-accessible
			STATUS current
			DESCRIPTION
				"Module TLE0001C01V1 Entry"
			INDEX { tle0001c01v1Index }
			::= { tle0001c01v1Table 1 }

			Tle0001c01v1Entry ::=
			SEQUENCE {
				tle0001c01v1Index
				ModuleIndex,
				tle0001c01v1App1Ena
				Bit0No1Yes,
				tle0001c01v1App2Ena
				Bit0No1Yes,
				tle0001c01v1App3Ena
				Bit0No1Yes,
				tle0001c01v1SerialNo
				SerialNo
			 }

		-- 1.3.6.1.4.1.10106.3.101291.1.1.1
		tle0001c01v1Index OBJECT-TYPE
			SYNTAX ModuleIndex
			MAX-ACCESS read-only
			STATUS current
			DESCRIPTION
				"Index of TLE0001C01V1 Table"
		::= { tle0001c01v1Entry 1 }

		-- 1.3.6.1.4.1.10106.3.101291.1.1.3
		tle0001c01v1App1Ena OBJECT-TYPE
			SYNTAX Bit0No1Yes
			MAX-ACCESS read-only
			STATUS current
			DESCRIPTION
				"Indicates the event log is enabled"
		::= { tle0001c01v1Entry 3 }

		-- 1.3.6.1.4.1.10106.3.101291.1.1.5
		tle0001c01v1App2Ena OBJECT-TYPE
			SYNTAX Bit0No1Yes
			MAX-ACCESS read-only
			STATUS current
			DESCRIPTION
				"Indicates the SNMP is enabled"
		::= { tle0001c01v1Entry 5 }

		-- 1.3.6.1.4.1.10106.3.101291.1.1.7
		tle0001c01v1App3Ena OBJECT-TYPE
			SYNTAX Bit0No1Yes
			MAX-ACCESS read-only
			STATUS current
			DESCRIPTION
				"Indicates the access control is enabled"
		::= { tle0001c01v1Entry 7 }

		-- 1.3.6.1.4.1.10106.3.101291.1.1.9
		tle0001c01v1SerialNo OBJECT-TYPE
			SYNTAX SerialNo
			MAX-ACCESS read-only
			STATUS current
			DESCRIPTION
				"Serial number"
		::= { tle0001c01v1Entry 9 }

		-- 1.3.6.1.4.1.10106.3.378901
		hdc3000c01v1 OBJECT IDENTIFIER ::= { albalaProducts 378901 }

		-- 1.3.6.1.4.1.10106.3.378901.1
		hdc3000c01v1Table  OBJECT-TYPE
			SYNTAX SEQUENCE OF Hdc3000c01v1Entry
			MAX-ACCESS not-accessible
			STATUS current
			DESCRIPTION
				"Module  HDC3000C01V1 Table"
			::= { hdc3000c01v1 1 }

		-- 1.3.6.1.4.1.10106.3.378901.1.1
		hdc3000c01v1Entry  OBJECT-TYPE
			SYNTAX Hdc3000c01v1Entry
			MAX-ACCESS not-accessible
			STATUS current
			DESCRIPTION
				"Module HDC3000C01V1 Entry"
			INDEX { hdc3000c01v1Index }
			::= { hdc3000c01v1Table 1 }

			Hdc3000c01v1Entry ::=
			SEQUENCE {
				hdc3000c01v1Index
				ModuleIndex,
				hdc3000c01v1ActivePreset
				Preset16Active,
				hdc3000c01v1LoadPreset
				Preset16Load,
				hdc3000c01v1SavePreset
				Preset16Save,
				hdc3000c01v1AnaRefFmt
				SdiHd3gFmt5,
				hdc3000c01v1AnaRefFmtTrapEnable
				AlarmEnable,
				hdc3000c01v1GenlockMode
				GenlockM0de2,
				hdc3000c01v1EnaAud20Bit
				Bit0No1Yes,
				hdc3000c01v1ModeConv
				Bit0Aut1Man,
				hdc3000c01v1ModeConvTrapEnable
				AlarmEnable,
				hdc3000c01v1OutAfd
				Afd1,
				hdc3000c01v1OutAfdTrapEnable
				AlarmEnable,
				hdc3000c01v1OutCf
				Cf1,
				hdc3000c01v1OutCfTrapEnable
				AlarmEnable,
				hdc3000c01v1InAfdExpct
				Afd1,
				hdc3000c01v1InAfdExpctTrapEnable
				AlarmEnable,
				hdc3000c01v1InCfExpct
				Cf1,
				hdc3000c01v1InCfExpctTrapEnable
				AlarmEnable,
				hdc3000c01v1OutsdEnaS2016
				Bit0No1Yes,
				hdc3000c01v1OutsdEnaVii
				Bit0No1Yes,
				hdc3000c01v1OutsdEnaWss
				Bit0No1Yes,
				hdc3000c01v1OutsdEnaVitc
				Bit0No1Yes,
				hdc3000c01v1OutsdEnaTxt
				Bit0No1Yes,
				hdc3000c01v1SelAudPair0
				AudioMxInput5,
				hdc3000c01v1SelAudPair1
				AudioMxInput5,
				hdc3000c01v1SelAudPair2
				AudioMxInput5,
				hdc3000c01v1SelAudPair3
				AudioMxInput5,
				hdc3000c01v1SelAudPair4
				AudioMxInput5,
				hdc3000c01v1SelAudPair5
				AudioMxInput5,
				hdc3000c01v1SelAudPair6
				AudioMxInput5,
				hdc3000c01v1SelAudPair7
				AudioMxInput5,
				hdc3000c01v1VDelay
				DelayLines2,
				hdc3000c01v1HDelay
				DelayPixel5,
				hdc3000c01v1VDelaySd
				DelayLines2,
				hdc3000c01v1HDelaySd
				DelayPixel5,
				hdc3000c01v1Grp1P0Gain
				Gain24dbMute,
				hdc3000c01v1Grp1P0Phase
				Bit0Nor1Inv,
				hdc3000c01v1Grp1P1Gain
				Gain24dbMute,
				hdc3000c01v1Grp1P1Phase
				Bit0Nor1Inv,
				hdc3000c01v1Grp2P0Gain
				Gain24dbMute,
				hdc3000c01v1Grp2P0Phase
				Bit0Nor1Inv,
				hdc3000c01v1Grp2P1Gain
				Gain24dbMute,
				hdc3000c01v1Grp2P1Phase
				Bit0Nor1Inv,
				hdc3000c01v1Grp3P0Gain
				Gain24dbMute,
				hdc3000c01v1Grp3P0Phase
				Bit0Nor1Inv,
				hdc3000c01v1Grp3P1Gain
				Gain24dbMute,
				hdc3000c01v1Grp3P1Phase
				Bit0Nor1Inv,
				hdc3000c01v1Grp4P0Gain
				Gain24dbMute,
				hdc3000c01v1Grp4P0Phase
				Bit0Nor1Inv,
				hdc3000c01v1Grp4P1Gain
				Gain24dbMute,
				hdc3000c01v1Grp4P1Phase
				Bit0Nor1Inv,
				hdc3000c01v1InAfdDetct
				Afd1,
				hdc3000c01v1InAfdDetctTrapEnable
				AlarmEnable,
				hdc3000c01v1InCfDetct
				Cf1,
				hdc3000c01v1InCfDetctTrapEnable
				AlarmEnable,
				hdc3000c01v1InPhyFail
				BitFail,
				hdc3000c01v1InPhyFailTrapEnable
				AlarmEnable,
				hdc3000c01v1InFmtFail
				BitFail,
				hdc3000c01v1InFmtFailTrapEnable
				AlarmEnable,
				hdc3000c01v1InIncFail
				BitFail,
				hdc3000c01v1InIncFailTrapEnable
				AlarmEnable,
				hdc3000c01v1InPresCrcFail
				BitFail,
				hdc3000c01v1InCrcFail
				BitFail,
				hdc3000c01v1InCrcFailTrapEnable
				AlarmEnable,
				hdc3000c01v1InPrsS352Fail
				BitFail,
				hdc3000c01v1InS352Fail
				BitFail,
				hdc3000c01v1PresS2016Fail
				BitFail,
				hdc3000c01v1ErrS2016Fail
				BitFail,
				hdc3000c01v1PresAudG1Fail
				BitFail,
				hdc3000c01v1PresAudG1FailTrapEnable
				AlarmEnable,
				hdc3000c01v1PresAudG2Fail
				BitFail,
				hdc3000c01v1PresAudG2FailTrapEnable
				AlarmEnable,
				hdc3000c01v1PresAudG3Fail
				BitFail,
				hdc3000c01v1PresAudG3FailTrapEnable
				AlarmEnable,
				hdc3000c01v1PresAudG4Fail
				BitFail,
				hdc3000c01v1PresAudG4FailTrapEnable
				AlarmEnable,
				hdc3000c01v1RefFail
				BitFail,
				hdc3000c01v1RefFailTrapEnable
				AlarmEnable,
				hdc3000c01v1RefFmtFail
				BitFail,
				hdc3000c01v1RefFmtFailTrapEnable
				AlarmEnable,
				hdc3000c01v1LockFail
				BitFail,
				hdc3000c01v1LockFailTrapEnable
				AlarmEnable,
				hdc3000c01v1AudPair0Fail
				BitFail,
				hdc3000c01v1AudPair0FailTrapEnable
				AlarmEnable,
				hdc3000c01v1AudPair1Fail
				BitFail,
				hdc3000c01v1AudPair1FailTrapEnable
				AlarmEnable,
				hdc3000c01v1AudPair2Fail
				BitFail,
				hdc3000c01v1AudPair2FailTrapEnable
				AlarmEnable,
				hdc3000c01v1AudPair3Fail
				BitFail,
				hdc3000c01v1AudPair3FailTrapEnable
				AlarmEnable,
				hdc3000c01v1AudPair4Fail
				BitFail,
				hdc3000c01v1AudPair4FailTrapEnable
				AlarmEnable,
				hdc3000c01v1AudPair5Fail
				BitFail,
				hdc3000c01v1AudPair5FailTrapEnable
				AlarmEnable,
				hdc3000c01v1AudPair6Fail
				BitFail,
				hdc3000c01v1AudPair6FailTrapEnable
				AlarmEnable,
				hdc3000c01v1AudPair7Fail
				BitFail,
				hdc3000c01v1AudPair7FailTrapEnable
				AlarmEnable,
				hdc3000c01v1InFormat
				SdiHd3gFmt3,
				hdc3000c01v1InFormatTrapEnable
				AlarmEnable,
				hdc3000c01v1RefFormat
				SdiHd3gFmt3,
				hdc3000c01v1RefFormatTrapEnable
				AlarmEnable,
				hdc3000c01v1Mute
				Bit0No1Yes,
				hdc3000c01v1Black
				Bit0No1Yes,
				hdc3000c01v1MuteSd
				Bit0No1Yes,
				hdc3000c01v1BlackSd
				Bit0No1Yes,
				hdc3000c01v1Gpi1
				Bit0Off1On,
				hdc3000c01v1Gpi2
				Bit0Off1On,
				hdc3000c01v1Gpi3
				Bit0Off1On,
				hdc3000c01v1Gpi4
				Bit0Off1On,
				hdc3000c01v1SerialNo
				SerialNo,
				hdc3000c01v1OutsdEnaCea608
				Bit0No1Yes
			 }

		-- 1.3.6.1.4.1.10106.3.101291.1.1.1
		hdc3000c01v1Index OBJECT-TYPE
			SYNTAX ModuleIndex
			MAX-ACCESS read-only
			STATUS current
			DESCRIPTION
				"Index of HDC3000C01V1 Table"
		::= { hdc3000c01v1Entry 1 }

		-- 1.3.6.1.4.1.10106.3.101291.1.1.3
		hdc3000c01v1ActivePreset OBJECT-TYPE
			SYNTAX Preset16Active
			MAX-ACCESS read-only
			STATUS current
			DESCRIPTION
				"Shows the active preset"
		::= { hdc3000c01v1Entry 3 }

		-- 1.3.6.1.4.1.10106.3.101291.1.1.5
		hdc3000c01v1LoadPreset OBJECT-TYPE
			SYNTAX Preset16Load
			MAX-ACCESS read-write
			STATUS current
			DESCRIPTION
				"Allows loading a preset"
		::= { hdc3000c01v1Entry 5 }

		-- 1.3.6.1.4.1.10106.3.101291.1.1.7
		hdc3000c01v1SavePreset OBJECT-TYPE
			SYNTAX Preset16Save
			MAX-ACCESS read-write
			STATUS current
			DESCRIPTION
				"Allows saving a preset"
		::= { hdc3000c01v1Entry 7 }

		-- 1.3.6.1.4.1.10106.3.101291.1.1.9
		hdc3000c01v1AnaRefFmt OBJECT-TYPE
			SYNTAX SdiHd3gFmt5
			MAX-ACCESS read-write
			STATUS current
			DESCRIPTION
				"Analog reference input format"
		::= { hdc3000c01v1Entry 9 }

		-- 1.3.6.1.4.1.10106.3.101291.1.1.10
		hdc3000c01v1AnaRefFmtTrapEnable OBJECT-TYPE
			SYNTAX AlarmEnable
			MAX-ACCESS read-write
			STATUS current
			DESCRIPTION
				"Analog reference input format Trap Enable"
		::= { hdc3000c01v1Entry 10 }

		-- 1.3.6.1.4.1.10106.3.101291.1.1.11
		hdc3000c01v1GenlockMode OBJECT-TYPE
			SYNTAX GenlockM0de2
			MAX-ACCESS read-write
			STATUS current
			DESCRIPTION
				"Allows selecting the reference input signal"
		::= { hdc3000c01v1Entry 11 }

		-- 1.3.6.1.4.1.10106.3.101291.1.1.13
		hdc3000c01v1EnaAud20Bit OBJECT-TYPE
			SYNTAX Bit0No1Yes
			MAX-ACCESS read-write
			STATUS current
			DESCRIPTION
				"Enable 20-bit audio instead of 24-bit"
		::= { hdc3000c01v1Entry 13 }

		-- 1.3.6.1.4.1.10106.3.101291.1.1.15
		hdc3000c01v1ModeConv OBJECT-TYPE
			SYNTAX Bit0Aut1Man
			MAX-ACCESS read-write
			STATUS current
			DESCRIPTION
				"Conversion mode"
		::= { hdc3000c01v1Entry 15 }

		-- 1.3.6.1.4.1.10106.3.101291.1.1.16
		hdc3000c01v1ModeConvTrapEnable OBJECT-TYPE
			SYNTAX AlarmEnable
			MAX-ACCESS read-write
			STATUS current
			DESCRIPTION
				"Conversion mode Trap Enable"
		::= { hdc3000c01v1Entry 16 }

		-- 1.3.6.1.4.1.10106.3.101291.1.1.17
		hdc3000c01v1OutAfd OBJECT-TYPE
			SYNTAX Afd1
			MAX-ACCESS read-write
			STATUS current
			DESCRIPTION
				"Output active format description"
		::= { hdc3000c01v1Entry 17 }

		-- 1.3.6.1.4.1.10106.3.101291.1.1.18
		hdc3000c01v1OutAfdTrapEnable OBJECT-TYPE
			SYNTAX AlarmEnable
			MAX-ACCESS read-write
			STATUS current
			DESCRIPTION
				"Output active format description Trap Enable"
		::= { hdc3000c01v1Entry 18 }

		-- 1.3.6.1.4.1.10106.3.101291.1.1.19
		hdc3000c01v1OutCf OBJECT-TYPE
			SYNTAX Cf1
			MAX-ACCESS read-write
			STATUS current
			DESCRIPTION
				"Output coded frame"
		::= { hdc3000c01v1Entry 19 }

		-- 1.3.6.1.4.1.10106.3.101291.1.1.20
		hdc3000c01v1OutCfTrapEnable OBJECT-TYPE
			SYNTAX AlarmEnable
			MAX-ACCESS read-write
			STATUS current
			DESCRIPTION
				"Output coded frame Trap Enable"
		::= { hdc3000c01v1Entry 20 }

		-- 1.3.6.1.4.1.10106.3.101291.1.1.21
		hdc3000c01v1InAfdExpct OBJECT-TYPE
			SYNTAX Afd1
			MAX-ACCESS read-write
			STATUS current
			DESCRIPTION
				"Input expected active format description"
		::= { hdc3000c01v1Entry 21 }

		-- 1.3.6.1.4.1.10106.3.101291.1.1.22
		hdc3000c01v1InAfdExpctTrapEnable OBJECT-TYPE
			SYNTAX AlarmEnable
			MAX-ACCESS read-write
			STATUS current
			DESCRIPTION
				"Input expected active format description Trap Enable"
		::= { hdc3000c01v1Entry 22 }

		-- 1.3.6.1.4.1.10106.3.101291.1.1.23
		hdc3000c01v1InCfExpct OBJECT-TYPE
			SYNTAX Cf1
			MAX-ACCESS read-write
			STATUS current
			DESCRIPTION
				"Input expected coded frame"
		::= { hdc3000c01v1Entry 23 }

		-- 1.3.6.1.4.1.10106.3.101291.1.1.24
		hdc3000c01v1InCfExpctTrapEnable OBJECT-TYPE
			SYNTAX AlarmEnable
			MAX-ACCESS read-write
			STATUS current
			DESCRIPTION
				"Input expected coded frame Trap Enable"
		::= { hdc3000c01v1Entry 24 }

		-- 1.3.6.1.4.1.10106.3.101291.1.1.25
		hdc3000c01v1OutsdEnaS2016 OBJECT-TYPE
			SYNTAX Bit0No1Yes
			MAX-ACCESS read-write
			STATUS current
			DESCRIPTION
				"Enables insertion of SMPTE 2016 packets in  OUTSD"
		::= { hdc3000c01v1Entry 25 }

		-- 1.3.6.1.4.1.10106.3.101291.1.1.27
		hdc3000c01v1OutsdEnaVii OBJECT-TYPE
			SYNTAX Bit0No1Yes
			MAX-ACCESS read-write
			STATUS current
			DESCRIPTION
				"Enables insertion of VII in OUTSD"
		::= { hdc3000c01v1Entry 27 }

		-- 1.3.6.1.4.1.10106.3.101291.1.1.29
		hdc3000c01v1OutsdEnaWss OBJECT-TYPE
			SYNTAX Bit0No1Yes
			MAX-ACCESS read-write
			STATUS current
			DESCRIPTION
				"Enables insertion of WSS in OUTSD"
		::= { hdc3000c01v1Entry 29 }

		-- 1.3.6.1.4.1.10106.3.101291.1.1.31
		hdc3000c01v1OutsdEnaVitc OBJECT-TYPE
			SYNTAX Bit0No1Yes
			MAX-ACCESS read-write
			STATUS current
			DESCRIPTION
				"Enables insertion of VITC in OUTSD"
		::= { hdc3000c01v1Entry 31 }

		-- 1.3.6.1.4.1.10106.3.101291.1.1.33
		hdc3000c01v1OutsdEnaTxt OBJECT-TYPE
			SYNTAX Bit0No1Yes
			MAX-ACCESS read-write
			STATUS current
			DESCRIPTION
				"Enables insertion of TXT in OUTSD"
		::= { hdc3000c01v1Entry 33 }

		-- 1.3.6.1.4.1.10106.3.101291.1.1.35
		hdc3000c01v1SelAudPair0 OBJECT-TYPE
			SYNTAX AudioMxInput5
			MAX-ACCESS read-write
			STATUS current
			DESCRIPTION
				"Selection of output audio for pair 0"
		::= { hdc3000c01v1Entry 35 }

		-- 1.3.6.1.4.1.10106.3.101291.1.1.37
		hdc3000c01v1SelAudPair1 OBJECT-TYPE
			SYNTAX AudioMxInput5
			MAX-ACCESS read-write
			STATUS current
			DESCRIPTION
				"Selection of output audio for pair 1"
		::= { hdc3000c01v1Entry 37 }

		-- 1.3.6.1.4.1.10106.3.101291.1.1.39
		hdc3000c01v1SelAudPair2 OBJECT-TYPE
			SYNTAX AudioMxInput5
			MAX-ACCESS read-write
			STATUS current
			DESCRIPTION
				"Selection of output audio for pair 2"
		::= { hdc3000c01v1Entry 39 }

		-- 1.3.6.1.4.1.10106.3.101291.1.1.41
		hdc3000c01v1SelAudPair3 OBJECT-TYPE
			SYNTAX AudioMxInput5
			MAX-ACCESS read-write
			STATUS current
			DESCRIPTION
				"Selection of output audio for pair 3"
		::= { hdc3000c01v1Entry 41 }

		-- 1.3.6.1.4.1.10106.3.101291.1.1.43
		hdc3000c01v1SelAudPair4 OBJECT-TYPE
			SYNTAX AudioMxInput5
			MAX-ACCESS read-write
			STATUS current
			DESCRIPTION
				"Selection of output audio for pair 4"
		::= { hdc3000c01v1Entry 43 }

		-- 1.3.6.1.4.1.10106.3.101291.1.1.45
		hdc3000c01v1SelAudPair5 OBJECT-TYPE
			SYNTAX AudioMxInput5
			MAX-ACCESS read-write
			STATUS current
			DESCRIPTION
				"Selection of output audio for pair 5"
		::= { hdc3000c01v1Entry 45 }

		-- 1.3.6.1.4.1.10106.3.101291.1.1.47
		hdc3000c01v1SelAudPair6 OBJECT-TYPE
			SYNTAX AudioMxInput5
			MAX-ACCESS read-write
			STATUS current
			DESCRIPTION
				"Selection of output audio for pair 6"
		::= { hdc3000c01v1Entry 47 }

		-- 1.3.6.1.4.1.10106.3.101291.1.1.49
		hdc3000c01v1SelAudPair7 OBJECT-TYPE
			SYNTAX AudioMxInput5
			MAX-ACCESS read-write
			STATUS current
			DESCRIPTION
				"Selection of output audio for pair 7"
		::= { hdc3000c01v1Entry 49 }

		-- 1.3.6.1.4.1.10106.3.101291.1.1.51
		hdc3000c01v1VDelay OBJECT-TYPE
			SYNTAX DelayLines2
			MAX-ACCESS read-write
			STATUS current
			DESCRIPTION
				"Allows adjusting the video vertical delay"
		::= { hdc3000c01v1Entry 51 }

		-- 1.3.6.1.4.1.10106.3.101291.1.1.53
		hdc3000c01v1HDelay OBJECT-TYPE
			SYNTAX DelayPixel5
			MAX-ACCESS read-write
			STATUS current
			DESCRIPTION
				"Allows adjusting the video horizontal delay"
		::= { hdc3000c01v1Entry 53 }

		-- 1.3.6.1.4.1.10106.3.101291.1.1.55
		hdc3000c01v1VDelaySd OBJECT-TYPE
			SYNTAX DelayLines2
			MAX-ACCESS read-write
			STATUS current
			DESCRIPTION
				"Allows adjusting the SD downconverted video vertical delay"
		::= { hdc3000c01v1Entry 55 }

		-- 1.3.6.1.4.1.10106.3.101291.1.1.57
		hdc3000c01v1HDelaySd OBJECT-TYPE
			SYNTAX DelayPixel5
			MAX-ACCESS read-write
			STATUS current
			DESCRIPTION
				"Allows adjusting the SD downconverted video horizontal delay"
		::= { hdc3000c01v1Entry 57 }

		-- 1.3.6.1.4.1.10106.3.101291.1.1.59
		hdc3000c01v1Grp1P0Gain OBJECT-TYPE
			SYNTAX Gain24dbMute
			MAX-ACCESS read-write
			STATUS current
			DESCRIPTION
				"Group 1 pair 0 gain"
		::= { hdc3000c01v1Entry 59 }

		-- 1.3.6.1.4.1.10106.3.101291.1.1.61
		hdc3000c01v1Grp1P0Phase OBJECT-TYPE
			SYNTAX Bit0Nor1Inv
			MAX-ACCESS read-write
			STATUS current
			DESCRIPTION
				"Group 1 pair 0 phase"
		::= { hdc3000c01v1Entry 61 }

		-- 1.3.6.1.4.1.10106.3.101291.1.1.63
		hdc3000c01v1Grp1P1Gain OBJECT-TYPE
			SYNTAX Gain24dbMute
			MAX-ACCESS read-write
			STATUS current
			DESCRIPTION
				"Group 1 pair 1 gain"
		::= { hdc3000c01v1Entry 63 }

		-- 1.3.6.1.4.1.10106.3.101291.1.1.65
		hdc3000c01v1Grp1P1Phase OBJECT-TYPE
			SYNTAX Bit0Nor1Inv
			MAX-ACCESS read-write
			STATUS current
			DESCRIPTION
				"Group 1 pair 1 phase"
		::= { hdc3000c01v1Entry 65 }

		-- 1.3.6.1.4.1.10106.3.101291.1.1.67
		hdc3000c01v1Grp2P0Gain OBJECT-TYPE
			SYNTAX Gain24dbMute
			MAX-ACCESS read-write
			STATUS current
			DESCRIPTION
				"Group 2 pair 0 gain"
		::= { hdc3000c01v1Entry 67 }

		-- 1.3.6.1.4.1.10106.3.101291.1.1.69
		hdc3000c01v1Grp2P0Phase OBJECT-TYPE
			SYNTAX Bit0Nor1Inv
			MAX-ACCESS read-write
			STATUS current
			DESCRIPTION
				"Group 2 pair 0 phase"
		::= { hdc3000c01v1Entry 69 }

		-- 1.3.6.1.4.1.10106.3.101291.1.1.71
		hdc3000c01v1Grp2P1Gain OBJECT-TYPE
			SYNTAX Gain24dbMute
			MAX-ACCESS read-write
			STATUS current
			DESCRIPTION
				"Group 2 pair 1 gain"
		::= { hdc3000c01v1Entry 71 }

		-- 1.3.6.1.4.1.10106.3.101291.1.1.73
		hdc3000c01v1Grp2P1Phase OBJECT-TYPE
			SYNTAX Bit0Nor1Inv
			MAX-ACCESS read-write
			STATUS current
			DESCRIPTION
				"Group 2 pair 1 phase"
		::= { hdc3000c01v1Entry 73 }

		-- 1.3.6.1.4.1.10106.3.101291.1.1.75
		hdc3000c01v1Grp3P0Gain OBJECT-TYPE
			SYNTAX Gain24dbMute
			MAX-ACCESS read-write
			STATUS current
			DESCRIPTION
				"Group 3 pair 0 gain"
		::= { hdc3000c01v1Entry 75 }

		-- 1.3.6.1.4.1.10106.3.101291.1.1.77
		hdc3000c01v1Grp3P0Phase OBJECT-TYPE
			SYNTAX Bit0Nor1Inv
			MAX-ACCESS read-write
			STATUS current
			DESCRIPTION
				"Group 3 pair 0 phase"
		::= { hdc3000c01v1Entry 77 }

		-- 1.3.6.1.4.1.10106.3.101291.1.1.79
		hdc3000c01v1Grp3P1Gain OBJECT-TYPE
			SYNTAX Gain24dbMute
			MAX-ACCESS read-write
			STATUS current
			DESCRIPTION
				"Group 3 pair 1 gain"
		::= { hdc3000c01v1Entry 79 }

		-- 1.3.6.1.4.1.10106.3.101291.1.1.81
		hdc3000c01v1Grp3P1Phase OBJECT-TYPE
			SYNTAX Bit0Nor1Inv
			MAX-ACCESS read-write
			STATUS current
			DESCRIPTION
				"Group 3 pair 1 phase"
		::= { hdc3000c01v1Entry 81 }

		-- 1.3.6.1.4.1.10106.3.101291.1.1.83
		hdc3000c01v1Grp4P0Gain OBJECT-TYPE
			SYNTAX Gain24dbMute
			MAX-ACCESS read-write
			STATUS current
			DESCRIPTION
				"Group 4 pair 0 gain"
		::= { hdc3000c01v1Entry 83 }

		-- 1.3.6.1.4.1.10106.3.101291.1.1.85
		hdc3000c01v1Grp4P0Phase OBJECT-TYPE
			SYNTAX Bit0Nor1Inv
			MAX-ACCESS read-write
			STATUS current
			DESCRIPTION
				"Group 4 pair 0 phase"
		::= { hdc3000c01v1Entry 85 }

		-- 1.3.6.1.4.1.10106.3.101291.1.1.87
		hdc3000c01v1Grp4P1Gain OBJECT-TYPE
			SYNTAX Gain24dbMute
			MAX-ACCESS read-write
			STATUS current
			DESCRIPTION
				"Group 4 pair 1 gain"
		::= { hdc3000c01v1Entry 87 }

		-- 1.3.6.1.4.1.10106.3.101291.1.1.89
		hdc3000c01v1Grp4P1Phase OBJECT-TYPE
			SYNTAX Bit0Nor1Inv
			MAX-ACCESS read-write
			STATUS current
			DESCRIPTION
				"Group 4 pair 1 phase"
		::= { hdc3000c01v1Entry 89 }

		-- 1.3.6.1.4.1.10106.3.101291.1.1.91
		hdc3000c01v1InAfdDetct OBJECT-TYPE
			SYNTAX Afd1
			MAX-ACCESS read-only
			STATUS current
			DESCRIPTION
				"Input detected AFD"
		::= { hdc3000c01v1Entry 91 }

		-- 1.3.6.1.4.1.10106.3.101291.1.1.92
		hdc3000c01v1InAfdDetctTrapEnable OBJECT-TYPE
			SYNTAX AlarmEnable
			MAX-ACCESS read-write
			STATUS current
			DESCRIPTION
				"Input detected AFD Trap Enable"
		::= { hdc3000c01v1Entry 92 }

		-- 1.3.6.1.4.1.10106.3.101291.1.1.93
		hdc3000c01v1InCfDetct OBJECT-TYPE
			SYNTAX Cf1
			MAX-ACCESS read-only
			STATUS current
			DESCRIPTION
				"Input detected coded frame"
		::= { hdc3000c01v1Entry 93 }

		-- 1.3.6.1.4.1.10106.3.101291.1.1.94
		hdc3000c01v1InCfDetctTrapEnable OBJECT-TYPE
			SYNTAX AlarmEnable
			MAX-ACCESS read-write
			STATUS current
			DESCRIPTION
				"Input detected coded frame Trap Enable"
		::= { hdc3000c01v1Entry 94 }

		-- 1.3.6.1.4.1.10106.3.101291.1.1.95
		hdc3000c01v1InPhyFail OBJECT-TYPE
			SYNTAX BitFail
			MAX-ACCESS read-only
			STATUS current
			DESCRIPTION
				"Absence fail"
		::= { hdc3000c01v1Entry 95 }

		-- 1.3.6.1.4.1.10106.3.101291.1.1.96
		hdc3000c01v1InPhyFailTrapEnable OBJECT-TYPE
			SYNTAX AlarmEnable
			MAX-ACCESS read-write
			STATUS current
			DESCRIPTION
				"Absence fail Trap Enable"
		::= { hdc3000c01v1Entry 96 }

		-- 1.3.6.1.4.1.10106.3.101291.1.1.97
		hdc3000c01v1InFmtFail OBJECT-TYPE
			SYNTAX BitFail
			MAX-ACCESS read-only
			STATUS current
			DESCRIPTION
				"Format fail"
		::= { hdc3000c01v1Entry 97 }

		-- 1.3.6.1.4.1.10106.3.101291.1.1.98
		hdc3000c01v1InFmtFailTrapEnable OBJECT-TYPE
			SYNTAX AlarmEnable
			MAX-ACCESS read-write
			STATUS current
			DESCRIPTION
				"Format fail Trap Enable"
		::= { hdc3000c01v1Entry 98 }

		-- 1.3.6.1.4.1.10106.3.101291.1.1.99
		hdc3000c01v1InIncFail OBJECT-TYPE
			SYNTAX BitFail
			MAX-ACCESS read-only
			STATUS current
			DESCRIPTION
				"Incompatible format fail"
		::= { hdc3000c01v1Entry 99 }

		-- 1.3.6.1.4.1.10106.3.101291.1.1.100
		hdc3000c01v1InIncFailTrapEnable OBJECT-TYPE
			SYNTAX AlarmEnable
			MAX-ACCESS read-write
			STATUS current
			DESCRIPTION
				"Incompatible format fail Trap Enable"
		::= { hdc3000c01v1Entry 100 }

		-- 1.3.6.1.4.1.10106.3.101291.1.1.101
		hdc3000c01v1InPresCrcFail OBJECT-TYPE
			SYNTAX BitFail
			MAX-ACCESS read-only
			STATUS current
			DESCRIPTION
				"EDH/CRC presence fail"
		::= { hdc3000c01v1Entry 101 }

		-- 1.3.6.1.4.1.10106.3.101291.1.1.103
		hdc3000c01v1InCrcFail OBJECT-TYPE
			SYNTAX BitFail
			MAX-ACCESS read-only
			STATUS current
			DESCRIPTION
				"EDH/CRC fail"
		::= { hdc3000c01v1Entry 103 }

		-- 1.3.6.1.4.1.10106.3.101291.1.1.104
		hdc3000c01v1InCrcFailTrapEnable OBJECT-TYPE
			SYNTAX AlarmEnable
			MAX-ACCESS read-write
			STATUS current
			DESCRIPTION
				"EDH/CRC fail Trap Enable"
		::= { hdc3000c01v1Entry 104 }

		-- 1.3.6.1.4.1.10106.3.101291.1.1.105
		hdc3000c01v1InPrsS352Fail OBJECT-TYPE
			SYNTAX BitFail
			MAX-ACCESS read-only
			STATUS current
			DESCRIPTION
				"SMPTE 352 presence fail"
		::= { hdc3000c01v1Entry 105 }

		-- 1.3.6.1.4.1.10106.3.101291.1.1.107
		hdc3000c01v1InS352Fail OBJECT-TYPE
			SYNTAX BitFail
			MAX-ACCESS read-only
			STATUS current
			DESCRIPTION
				"SMPTE 352 fail"
		::= { hdc3000c01v1Entry 107 }

		-- 1.3.6.1.4.1.10106.3.101291.1.1.109
		hdc3000c01v1PresS2016Fail OBJECT-TYPE
			SYNTAX BitFail
			MAX-ACCESS read-only
			STATUS current
			DESCRIPTION
				"SMPTE 2016 presence fail"
		::= { hdc3000c01v1Entry 109 }

		-- 1.3.6.1.4.1.10106.3.101291.1.1.111
		hdc3000c01v1ErrS2016Fail OBJECT-TYPE
			SYNTAX BitFail
			MAX-ACCESS read-only
			STATUS current
			DESCRIPTION
				"SMPTE 2016 error fail"
		::= { hdc3000c01v1Entry 111 }

		-- 1.3.6.1.4.1.10106.3.101291.1.1.113
		hdc3000c01v1PresAudG1Fail OBJECT-TYPE
			SYNTAX BitFail
			MAX-ACCESS read-only
			STATUS current
			DESCRIPTION
				"Audio group 1 presence fail"
		::= { hdc3000c01v1Entry 113 }

		-- 1.3.6.1.4.1.10106.3.101291.1.1.114
		hdc3000c01v1PresAudG1FailTrapEnable OBJECT-TYPE
			SYNTAX AlarmEnable
			MAX-ACCESS read-write
			STATUS current
			DESCRIPTION
				"Audio group 1 presence fail Trap Enable"
		::= { hdc3000c01v1Entry 114 }

		-- 1.3.6.1.4.1.10106.3.101291.1.1.115
		hdc3000c01v1PresAudG2Fail OBJECT-TYPE
			SYNTAX BitFail
			MAX-ACCESS read-only
			STATUS current
			DESCRIPTION
				"Audio group 2 presence fail"
		::= { hdc3000c01v1Entry 115 }

		-- 1.3.6.1.4.1.10106.3.101291.1.1.116
		hdc3000c01v1PresAudG2FailTrapEnable OBJECT-TYPE
			SYNTAX AlarmEnable
			MAX-ACCESS read-write
			STATUS current
			DESCRIPTION
				"Audio group 2 presence fail Trap Enable"
		::= { hdc3000c01v1Entry 116 }

		-- 1.3.6.1.4.1.10106.3.101291.1.1.117
		hdc3000c01v1PresAudG3Fail OBJECT-TYPE
			SYNTAX BitFail
			MAX-ACCESS read-only
			STATUS current
			DESCRIPTION
				"Audio group 3 presence fail"
		::= { hdc3000c01v1Entry 117 }

		-- 1.3.6.1.4.1.10106.3.101291.1.1.118
		hdc3000c01v1PresAudG3FailTrapEnable OBJECT-TYPE
			SYNTAX AlarmEnable
			MAX-ACCESS read-write
			STATUS current
			DESCRIPTION
				"Audio group 3 presence fail Trap Enable"
		::= { hdc3000c01v1Entry 118 }

		-- 1.3.6.1.4.1.10106.3.101291.1.1.119
		hdc3000c01v1PresAudG4Fail OBJECT-TYPE
			SYNTAX BitFail
			MAX-ACCESS read-only
			STATUS current
			DESCRIPTION
				"Audio group 4 presence fail"
		::= { hdc3000c01v1Entry 119 }

		-- 1.3.6.1.4.1.10106.3.101291.1.1.120
		hdc3000c01v1PresAudG4FailTrapEnable OBJECT-TYPE
			SYNTAX AlarmEnable
			MAX-ACCESS read-write
			STATUS current
			DESCRIPTION
				"Audio group 4 presence fail Trap Enable"
		::= { hdc3000c01v1Entry 120 }

		-- 1.3.6.1.4.1.10106.3.101291.1.1.121
		hdc3000c01v1RefFail OBJECT-TYPE
			SYNTAX BitFail
			MAX-ACCESS read-only
			STATUS current
			DESCRIPTION
				"Analog reference absence fail"
		::= { hdc3000c01v1Entry 121 }

		-- 1.3.6.1.4.1.10106.3.101291.1.1.122
		hdc3000c01v1RefFailTrapEnable OBJECT-TYPE
			SYNTAX AlarmEnable
			MAX-ACCESS read-write
			STATUS current
			DESCRIPTION
				"Analog reference absence fail Trap Enable"
		::= { hdc3000c01v1Entry 122 }

		-- 1.3.6.1.4.1.10106.3.101291.1.1.123
		hdc3000c01v1RefFmtFail OBJECT-TYPE
			SYNTAX BitFail
			MAX-ACCESS read-only
			STATUS current
			DESCRIPTION
				"Analog reference format fail"
		::= { hdc3000c01v1Entry 123 }

		-- 1.3.6.1.4.1.10106.3.101291.1.1.124
		hdc3000c01v1RefFmtFailTrapEnable OBJECT-TYPE
			SYNTAX AlarmEnable
			MAX-ACCESS read-write
			STATUS current
			DESCRIPTION
				"Analog reference format fail Trap Enable"
		::= { hdc3000c01v1Entry 124 }

		-- 1.3.6.1.4.1.10106.3.101291.1.1.125
		hdc3000c01v1LockFail OBJECT-TYPE
			SYNTAX BitFail
			MAX-ACCESS read-only
			STATUS current
			DESCRIPTION
				"Reference unlock fail"
		::= { hdc3000c01v1Entry 125 }

		-- 1.3.6.1.4.1.10106.3.101291.1.1.126
		hdc3000c01v1LockFailTrapEnable OBJECT-TYPE
			SYNTAX AlarmEnable
			MAX-ACCESS read-write
			STATUS current
			DESCRIPTION
				"Reference unlock fail Trap Enable"
		::= { hdc3000c01v1Entry 126 }

		-- 1.3.6.1.4.1.10106.3.101291.1.1.127
		hdc3000c01v1AudPair0Fail OBJECT-TYPE
			SYNTAX BitFail
			MAX-ACCESS read-only
			STATUS current
			DESCRIPTION
				"Audio pair 0 fail"
		::= { hdc3000c01v1Entry 127 }

		-- 1.3.6.1.4.1.10106.3.101291.1.1.128
		hdc3000c01v1AudPair0FailTrapEnable OBJECT-TYPE
			SYNTAX AlarmEnable
			MAX-ACCESS read-write
			STATUS current
			DESCRIPTION
				"Audio pair 0 fail Trap Enable"
		::= { hdc3000c01v1Entry 128 }

		-- 1.3.6.1.4.1.10106.3.101291.1.1.129
		hdc3000c01v1AudPair1Fail OBJECT-TYPE
			SYNTAX BitFail
			MAX-ACCESS read-only
			STATUS current
			DESCRIPTION
				"Audio pair 1 fail"
		::= { hdc3000c01v1Entry 129 }

		-- 1.3.6.1.4.1.10106.3.101291.1.1.130
		hdc3000c01v1AudPair1FailTrapEnable OBJECT-TYPE
			SYNTAX AlarmEnable
			MAX-ACCESS read-write
			STATUS current
			DESCRIPTION
				"Audio pair 1 fail Trap Enable"
		::= { hdc3000c01v1Entry 130 }

		-- 1.3.6.1.4.1.10106.3.101291.1.1.131
		hdc3000c01v1AudPair2Fail OBJECT-TYPE
			SYNTAX BitFail
			MAX-ACCESS read-only
			STATUS current
			DESCRIPTION
				"Audio pair 2 fail"
		::= { hdc3000c01v1Entry 131 }

		-- 1.3.6.1.4.1.10106.3.101291.1.1.132
		hdc3000c01v1AudPair2FailTrapEnable OBJECT-TYPE
			SYNTAX AlarmEnable
			MAX-ACCESS read-write
			STATUS current
			DESCRIPTION
				"Audio pair 2 fail Trap Enable"
		::= { hdc3000c01v1Entry 132 }

		-- 1.3.6.1.4.1.10106.3.101291.1.1.133
		hdc3000c01v1AudPair3Fail OBJECT-TYPE
			SYNTAX BitFail
			MAX-ACCESS read-only
			STATUS current
			DESCRIPTION
				"Audio pair 3 fail"
		::= { hdc3000c01v1Entry 133 }

		-- 1.3.6.1.4.1.10106.3.101291.1.1.134
		hdc3000c01v1AudPair3FailTrapEnable OBJECT-TYPE
			SYNTAX AlarmEnable
			MAX-ACCESS read-write
			STATUS current
			DESCRIPTION
				"Audio pair 3 fail Trap Enable"
		::= { hdc3000c01v1Entry 134 }

		-- 1.3.6.1.4.1.10106.3.101291.1.1.135
		hdc3000c01v1AudPair4Fail OBJECT-TYPE
			SYNTAX BitFail
			MAX-ACCESS read-only
			STATUS current
			DESCRIPTION
				"Audio pair 4 fail"
		::= { hdc3000c01v1Entry 135 }

		-- 1.3.6.1.4.1.10106.3.101291.1.1.136
		hdc3000c01v1AudPair4FailTrapEnable OBJECT-TYPE
			SYNTAX AlarmEnable
			MAX-ACCESS read-write
			STATUS current
			DESCRIPTION
				"Audio pair 4 fail Trap Enable"
		::= { hdc3000c01v1Entry 136 }

		-- 1.3.6.1.4.1.10106.3.101291.1.1.137
		hdc3000c01v1AudPair5Fail OBJECT-TYPE
			SYNTAX BitFail
			MAX-ACCESS read-only
			STATUS current
			DESCRIPTION
				"Audio pair 5 fail"
		::= { hdc3000c01v1Entry 137 }

		-- 1.3.6.1.4.1.10106.3.101291.1.1.138
		hdc3000c01v1AudPair5FailTrapEnable OBJECT-TYPE
			SYNTAX AlarmEnable
			MAX-ACCESS read-write
			STATUS current
			DESCRIPTION
				"Audio pair 5 fail Trap Enable"
		::= { hdc3000c01v1Entry 138 }

		-- 1.3.6.1.4.1.10106.3.101291.1.1.139
		hdc3000c01v1AudPair6Fail OBJECT-TYPE
			SYNTAX BitFail
			MAX-ACCESS read-only
			STATUS current
			DESCRIPTION
				"Audio pair 6 fail"
		::= { hdc3000c01v1Entry 139 }

		-- 1.3.6.1.4.1.10106.3.101291.1.1.140
		hdc3000c01v1AudPair6FailTrapEnable OBJECT-TYPE
			SYNTAX AlarmEnable
			MAX-ACCESS read-write
			STATUS current
			DESCRIPTION
				"Audio pair 6 fail Trap Enable"
		::= { hdc3000c01v1Entry 140 }

		-- 1.3.6.1.4.1.10106.3.101291.1.1.141
		hdc3000c01v1AudPair7Fail OBJECT-TYPE
			SYNTAX BitFail
			MAX-ACCESS read-only
			STATUS current
			DESCRIPTION
				"Audio pair 7 fail"
		::= { hdc3000c01v1Entry 141 }

		-- 1.3.6.1.4.1.10106.3.101291.1.1.142
		hdc3000c01v1AudPair7FailTrapEnable OBJECT-TYPE
			SYNTAX AlarmEnable
			MAX-ACCESS read-write
			STATUS current
			DESCRIPTION
				"Audio pair 7 fail Trap Enable"
		::= { hdc3000c01v1Entry 142 }

		-- 1.3.6.1.4.1.10106.3.101291.1.1.143
		hdc3000c01v1InFormat OBJECT-TYPE
			SYNTAX SdiHd3gFmt3
			MAX-ACCESS read-only
			STATUS current
			DESCRIPTION
				"Input format"
		::= { hdc3000c01v1Entry 143 }

		-- 1.3.6.1.4.1.10106.3.101291.1.1.144
		hdc3000c01v1InFormatTrapEnable OBJECT-TYPE
			SYNTAX AlarmEnable
			MAX-ACCESS read-write
			STATUS current
			DESCRIPTION
				"Input format Trap Enable"
		::= { hdc3000c01v1Entry 144 }

		-- 1.3.6.1.4.1.10106.3.101291.1.1.145
		hdc3000c01v1RefFormat OBJECT-TYPE
			SYNTAX SdiHd3gFmt3
			MAX-ACCESS read-only
			STATUS current
			DESCRIPTION
				"Reference format"
		::= { hdc3000c01v1Entry 145 }

		-- 1.3.6.1.4.1.10106.3.101291.1.1.146
		hdc3000c01v1RefFormatTrapEnable OBJECT-TYPE
			SYNTAX AlarmEnable
			MAX-ACCESS read-write
			STATUS current
			DESCRIPTION
				"Reference format Trap Enable"
		::= { hdc3000c01v1Entry 146 }

		-- 1.3.6.1.4.1.10106.3.101291.1.1.147
		hdc3000c01v1Mute OBJECT-TYPE
			SYNTAX Bit0No1Yes
			MAX-ACCESS read-only
			STATUS current
			DESCRIPTION
				"Muted output"
		::= { hdc3000c01v1Entry 147 }

		-- 1.3.6.1.4.1.10106.3.101291.1.1.149
		hdc3000c01v1Black OBJECT-TYPE
			SYNTAX Bit0No1Yes
			MAX-ACCESS read-only
			STATUS current
			DESCRIPTION
				"Black output"
		::= { hdc3000c01v1Entry 149 }

		-- 1.3.6.1.4.1.10106.3.101291.1.1.151
		hdc3000c01v1MuteSd OBJECT-TYPE
			SYNTAX Bit0No1Yes
			MAX-ACCESS read-only
			STATUS current
			DESCRIPTION
				"Muted SD output"
		::= { hdc3000c01v1Entry 151 }

		-- 1.3.6.1.4.1.10106.3.101291.1.1.153
		hdc3000c01v1BlackSd OBJECT-TYPE
			SYNTAX Bit0No1Yes
			MAX-ACCESS read-only
			STATUS current
			DESCRIPTION
				"Black SD output"
		::= { hdc3000c01v1Entry 153 }

		-- 1.3.6.1.4.1.10106.3.101291.1.1.155
		hdc3000c01v1Gpi1 OBJECT-TYPE
			SYNTAX Bit0Off1On
			MAX-ACCESS read-only
			STATUS current
			DESCRIPTION
				"Transmitted GPI1"
		::= { hdc3000c01v1Entry 155 }

		-- 1.3.6.1.4.1.10106.3.101291.1.1.157
		hdc3000c01v1Gpi2 OBJECT-TYPE
			SYNTAX Bit0Off1On
			MAX-ACCESS read-only
			STATUS current
			DESCRIPTION
				"Transmitted GPI2"
		::= { hdc3000c01v1Entry 157 }

		-- 1.3.6.1.4.1.10106.3.101291.1.1.159
		hdc3000c01v1Gpi3 OBJECT-TYPE
			SYNTAX Bit0Off1On
			MAX-ACCESS read-only
			STATUS current
			DESCRIPTION
				"Transmitted GPI3"
		::= { hdc3000c01v1Entry 159 }

		-- 1.3.6.1.4.1.10106.3.101291.1.1.161
		hdc3000c01v1Gpi4 OBJECT-TYPE
			SYNTAX Bit0Off1On
			MAX-ACCESS read-only
			STATUS current
			DESCRIPTION
				"Transmitted GPI4"
		::= { hdc3000c01v1Entry 161 }

		-- 1.3.6.1.4.1.10106.3.101291.1.1.163
		hdc3000c01v1SerialNo OBJECT-TYPE
			SYNTAX SerialNo
			MAX-ACCESS read-only
			STATUS current
			DESCRIPTION
				"Serial number"
		::= { hdc3000c01v1Entry 163 }

		-- 1.3.6.1.4.1.10106.3.101291.1.1.165
		hdc3000c01v1OutsdEnaCea608 OBJECT-TYPE
			SYNTAX Bit0No1Yes
			MAX-ACCESS read-write
			STATUS current
			DESCRIPTION
				"Enables insertion of CEA608 in OUTSD"
		::= { hdc3000c01v1Entry 165 }

		-- 1.3.6.1.4.1.10106.3.379801
		hli3000c01v1 OBJECT IDENTIFIER ::= { albalaProducts 379801 }

		-- 1.3.6.1.4.1.10106.3.379801.1
		hli3000c01v1Table  OBJECT-TYPE
			SYNTAX SEQUENCE OF Hli3000c01v1Entry
			MAX-ACCESS not-accessible
			STATUS current
			DESCRIPTION
				"Module  HLI3000C01V1 Table"
			::= { hli3000c01v1 1 }

		-- 1.3.6.1.4.1.10106.3.379801.1.1
		hli3000c01v1Entry  OBJECT-TYPE
			SYNTAX Hli3000c01v1Entry
			MAX-ACCESS not-accessible
			STATUS current
			DESCRIPTION
				"Module HLI3000C01V1 Entry"
			INDEX { hli3000c01v1Index }
			::= { hli3000c01v1Table 1 }

			Hli3000c01v1Entry ::=
			SEQUENCE {
				hli3000c01v1Index
				ModuleIndex,
				hli3000c01v1ActivePreset
				Preset16Active,
				hli3000c01v1LoadPreset
				Preset16Load,
				hli3000c01v1SavePreset
				Preset16Save,
				hli3000c01v1PgmInsLogo1
				Bit0No1Yes,
				hli3000c01v1PgmInsLogo1TrapEnable
				AlarmEnable,
				hli3000c01v1PgmInsLogo2
				Bit0No1Yes,
				hli3000c01v1PgmInsLogo2TrapEnable
				AlarmEnable,
				hli3000c01v1PgmInsLogo3
				Bit0No1Yes,
				hli3000c01v1PgmInsLogo3TrapEnable
				AlarmEnable,
				hli3000c01v1PgmInsLogo4
				Bit0No1Yes,
				hli3000c01v1PgmInsLogo4TrapEnable
				AlarmEnable,
				hli3000c01v1PvwInsLogo1
				Bit0No1Yes,
				hli3000c01v1PvwInsLogo2
				Bit0No1Yes,
				hli3000c01v1PvwInsLogo3
				Bit0No1Yes,
				hli3000c01v1PvwInsLogo4
				Bit0No1Yes,
				hli3000c01v1SelLogo1
				Uint8,
				hli3000c01v1SelLogo1TrapEnable
				AlarmEnable,
				hli3000c01v1SelLogo2
				Uint8,
				hli3000c01v1SelLogo2TrapEnable
				AlarmEnable,
				hli3000c01v1SelLogo3
				Uint8,
				hli3000c01v1SelLogo3TrapEnable
				AlarmEnable,
				hli3000c01v1SelLogo4
				Uint8,
				hli3000c01v1SelLogo4TrapEnable
				AlarmEnable,
				hli3000c01v1PosHLogo1
				Uint11,
				hli3000c01v1PosVLogo1
				Uint11,
				hli3000c01v1PosHLogo2
				Uint11,
				hli3000c01v1PosVLogo2
				Uint11,
				hli3000c01v1PosHLogo3
				Uint11,
				hli3000c01v1PosVLogo3
				Uint11,
				hli3000c01v1PosHLogo4
				Uint11,
				hli3000c01v1PosVLogo4
				Uint11,
				hli3000c01v1InputFPresSel
				Preset16Default,
				hli3000c01v1NoSignal
				BitFail,
				hli3000c01v1NoSignalTrapEnable
				AlarmEnable,
				hli3000c01v1Unlock
				BitFail,
				hli3000c01v1UnlockTrapEnable
				AlarmEnable,
				hli3000c01v1EdhError
				BitFail,
				hli3000c01v1EdhErrorTrapEnable
				AlarmEnable,
				hli3000c01v1Format
				SdiHd3gFmt3,
				hli3000c01v1FormatTrapEnable
				AlarmEnable,
				hli3000c01v1Gpi1
				Bit0Off1On,
				hli3000c01v1Gpi1TrapEnable
				AlarmEnable,
				hli3000c01v1Gpi2
				Bit0Off1On,
				hli3000c01v1Gpi2TrapEnable
				AlarmEnable,
				hli3000c01v1Gpi3
				Bit0Off1On,
				hli3000c01v1Gpi3TrapEnable
				AlarmEnable,
				hli3000c01v1Gpi4
				Bit0Off1On,
				hli3000c01v1Gpi4TrapEnable
				AlarmEnable,
				hli3000c01v1Gpi5
				Bit0Off1On,
				hli3000c01v1Gpi5TrapEnable
				AlarmEnable,
				hli3000c01v1Gpi6
				Bit0Off1On,
				hli3000c01v1Gpi6TrapEnable
				AlarmEnable,
				hli3000c01v1Gpi7
				Bit0Off1On,
				hli3000c01v1Gpi7TrapEnable
				AlarmEnable,
				hli3000c01v1Gpi8
				Bit0Off1On,
				hli3000c01v1Gpi8TrapEnable
				AlarmEnable,
				hli3000c01v1LdLogo1Stat
				HliLdStat,
				hli3000c01v1LdLogo2Stat
				HliLdStat,
				hli3000c01v1LdLogo3Stat
				HliLdStat,
				hli3000c01v1LdLogo4Stat
				HliLdStat,
				hli3000c01v1SerialNo
				SerialNo
			 }

		-- 1.3.6.1.4.1.10106.3.101291.1.1.1
		hli3000c01v1Index OBJECT-TYPE
			SYNTAX ModuleIndex
			MAX-ACCESS read-only
			STATUS current
			DESCRIPTION
				"Index of HLI3000C01V1 Table"
		::= { hli3000c01v1Entry 1 }

		-- 1.3.6.1.4.1.10106.3.101291.1.1.3
		hli3000c01v1ActivePreset OBJECT-TYPE
			SYNTAX Preset16Active
			MAX-ACCESS read-only
			STATUS current
			DESCRIPTION
				"Shows the active preset"
		::= { hli3000c01v1Entry 3 }

		-- 1.3.6.1.4.1.10106.3.101291.1.1.5
		hli3000c01v1LoadPreset OBJECT-TYPE
			SYNTAX Preset16Load
			MAX-ACCESS read-write
			STATUS current
			DESCRIPTION
				"Allows loading a preset"
		::= { hli3000c01v1Entry 5 }

		-- 1.3.6.1.4.1.10106.3.101291.1.1.7
		hli3000c01v1SavePreset OBJECT-TYPE
			SYNTAX Preset16Save
			MAX-ACCESS read-write
			STATUS current
			DESCRIPTION
				"Allows saving a preset"
		::= { hli3000c01v1Entry 7 }

		-- 1.3.6.1.4.1.10106.3.101291.1.1.9
		hli3000c01v1PgmInsLogo1 OBJECT-TYPE
			SYNTAX Bit0No1Yes
			MAX-ACCESS read-write
			STATUS current
			DESCRIPTION
				"Allows inserting the logo in the program output"
		::= { hli3000c01v1Entry 9 }

		-- 1.3.6.1.4.1.10106.3.101291.1.1.10
		hli3000c01v1PgmInsLogo1TrapEnable OBJECT-TYPE
			SYNTAX AlarmEnable
			MAX-ACCESS read-write
			STATUS current
			DESCRIPTION
				"Allows inserting the logo in the program output Trap Enable"
		::= { hli3000c01v1Entry 10 }

		-- 1.3.6.1.4.1.10106.3.101291.1.1.11
		hli3000c01v1PgmInsLogo2 OBJECT-TYPE
			SYNTAX Bit0No1Yes
			MAX-ACCESS read-write
			STATUS current
			DESCRIPTION
				"Allows inserting the logo in the program output"
		::= { hli3000c01v1Entry 11 }

		-- 1.3.6.1.4.1.10106.3.101291.1.1.12
		hli3000c01v1PgmInsLogo2TrapEnable OBJECT-TYPE
			SYNTAX AlarmEnable
			MAX-ACCESS read-write
			STATUS current
			DESCRIPTION
				"Allows inserting the logo in the program output Trap Enable"
		::= { hli3000c01v1Entry 12 }

		-- 1.3.6.1.4.1.10106.3.101291.1.1.13
		hli3000c01v1PgmInsLogo3 OBJECT-TYPE
			SYNTAX Bit0No1Yes
			MAX-ACCESS read-write
			STATUS current
			DESCRIPTION
				"Allows inserting the logo in the program output"
		::= { hli3000c01v1Entry 13 }

		-- 1.3.6.1.4.1.10106.3.101291.1.1.14
		hli3000c01v1PgmInsLogo3TrapEnable OBJECT-TYPE
			SYNTAX AlarmEnable
			MAX-ACCESS read-write
			STATUS current
			DESCRIPTION
				"Allows inserting the logo in the program output Trap Enable"
		::= { hli3000c01v1Entry 14 }

		-- 1.3.6.1.4.1.10106.3.101291.1.1.15
		hli3000c01v1PgmInsLogo4 OBJECT-TYPE
			SYNTAX Bit0No1Yes
			MAX-ACCESS read-write
			STATUS current
			DESCRIPTION
				"Allows inserting the logo in the program output"
		::= { hli3000c01v1Entry 15 }

		-- 1.3.6.1.4.1.10106.3.101291.1.1.16
		hli3000c01v1PgmInsLogo4TrapEnable OBJECT-TYPE
			SYNTAX AlarmEnable
			MAX-ACCESS read-write
			STATUS current
			DESCRIPTION
				"Allows inserting the logo in the program output Trap Enable"
		::= { hli3000c01v1Entry 16 }

		-- 1.3.6.1.4.1.10106.3.101291.1.1.17
		hli3000c01v1PvwInsLogo1 OBJECT-TYPE
			SYNTAX Bit0No1Yes
			MAX-ACCESS read-write
			STATUS current
			DESCRIPTION
				"Allows inserting the logo in the preview output"
		::= { hli3000c01v1Entry 17 }

		-- 1.3.6.1.4.1.10106.3.101291.1.1.19
		hli3000c01v1PvwInsLogo2 OBJECT-TYPE
			SYNTAX Bit0No1Yes
			MAX-ACCESS read-write
			STATUS current
			DESCRIPTION
				"Allows inserting the logo in the preview output"
		::= { hli3000c01v1Entry 19 }

		-- 1.3.6.1.4.1.10106.3.101291.1.1.21
		hli3000c01v1PvwInsLogo3 OBJECT-TYPE
			SYNTAX Bit0No1Yes
			MAX-ACCESS read-write
			STATUS current
			DESCRIPTION
				"Allows inserting the logo in the preview output"
		::= { hli3000c01v1Entry 21 }

		-- 1.3.6.1.4.1.10106.3.101291.1.1.23
		hli3000c01v1PvwInsLogo4 OBJECT-TYPE
			SYNTAX Bit0No1Yes
			MAX-ACCESS read-write
			STATUS current
			DESCRIPTION
				"Allows inserting the logo in the preview output"
		::= { hli3000c01v1Entry 23 }

		-- 1.3.6.1.4.1.10106.3.101291.1.1.25
		hli3000c01v1SelLogo1 OBJECT-TYPE
			SYNTAX Uint8
			MAX-ACCESS read-write
			STATUS current
			DESCRIPTION
				"Allows selecting the logo to be inserted"
		::= { hli3000c01v1Entry 25 }

		-- 1.3.6.1.4.1.10106.3.101291.1.1.26
		hli3000c01v1SelLogo1TrapEnable OBJECT-TYPE
			SYNTAX AlarmEnable
			MAX-ACCESS read-write
			STATUS current
			DESCRIPTION
				"Allows selecting the logo to be inserted Trap Enable"
		::= { hli3000c01v1Entry 26 }

		-- 1.3.6.1.4.1.10106.3.101291.1.1.27
		hli3000c01v1SelLogo2 OBJECT-TYPE
			SYNTAX Uint8
			MAX-ACCESS read-write
			STATUS current
			DESCRIPTION
				"Allows selecting the logo to be inserted"
		::= { hli3000c01v1Entry 27 }

		-- 1.3.6.1.4.1.10106.3.101291.1.1.28
		hli3000c01v1SelLogo2TrapEnable OBJECT-TYPE
			SYNTAX AlarmEnable
			MAX-ACCESS read-write
			STATUS current
			DESCRIPTION
				"Allows selecting the logo to be inserted Trap Enable"
		::= { hli3000c01v1Entry 28 }

		-- 1.3.6.1.4.1.10106.3.101291.1.1.29
		hli3000c01v1SelLogo3 OBJECT-TYPE
			SYNTAX Uint8
			MAX-ACCESS read-write
			STATUS current
			DESCRIPTION
				"Allows selecting the logo to be inserted"
		::= { hli3000c01v1Entry 29 }

		-- 1.3.6.1.4.1.10106.3.101291.1.1.30
		hli3000c01v1SelLogo3TrapEnable OBJECT-TYPE
			SYNTAX AlarmEnable
			MAX-ACCESS read-write
			STATUS current
			DESCRIPTION
				"Allows selecting the logo to be inserted Trap Enable"
		::= { hli3000c01v1Entry 30 }

		-- 1.3.6.1.4.1.10106.3.101291.1.1.31
		hli3000c01v1SelLogo4 OBJECT-TYPE
			SYNTAX Uint8
			MAX-ACCESS read-write
			STATUS current
			DESCRIPTION
				"Allows selecting the logo to be inserted"
		::= { hli3000c01v1Entry 31 }

		-- 1.3.6.1.4.1.10106.3.101291.1.1.32
		hli3000c01v1SelLogo4TrapEnable OBJECT-TYPE
			SYNTAX AlarmEnable
			MAX-ACCESS read-write
			STATUS current
			DESCRIPTION
				"Allows selecting the logo to be inserted Trap Enable"
		::= { hli3000c01v1Entry 32 }

		-- 1.3.6.1.4.1.10106.3.101291.1.1.33
		hli3000c01v1PosHLogo1 OBJECT-TYPE
			SYNTAX Uint11
			MAX-ACCESS read-write
			STATUS current
			DESCRIPTION
				"Allows adjust of logo horizontal position"
		::= { hli3000c01v1Entry 33 }

		-- 1.3.6.1.4.1.10106.3.101291.1.1.35
		hli3000c01v1PosVLogo1 OBJECT-TYPE
			SYNTAX Uint11
			MAX-ACCESS read-write
			STATUS current
			DESCRIPTION
				"Allows adjust of logo vertical position"
		::= { hli3000c01v1Entry 35 }

		-- 1.3.6.1.4.1.10106.3.101291.1.1.37
		hli3000c01v1PosHLogo2 OBJECT-TYPE
			SYNTAX Uint11
			MAX-ACCESS read-write
			STATUS current
			DESCRIPTION
				"Allows adjust of logo horizontal position"
		::= { hli3000c01v1Entry 37 }

		-- 1.3.6.1.4.1.10106.3.101291.1.1.39
		hli3000c01v1PosVLogo2 OBJECT-TYPE
			SYNTAX Uint11
			MAX-ACCESS read-write
			STATUS current
			DESCRIPTION
				"Allows adjust of logo vertical position"
		::= { hli3000c01v1Entry 39 }

		-- 1.3.6.1.4.1.10106.3.101291.1.1.41
		hli3000c01v1PosHLogo3 OBJECT-TYPE
			SYNTAX Uint11
			MAX-ACCESS read-write
			STATUS current
			DESCRIPTION
				"Allows adjust of logo horizontal position"
		::= { hli3000c01v1Entry 41 }

		-- 1.3.6.1.4.1.10106.3.101291.1.1.43
		hli3000c01v1PosVLogo3 OBJECT-TYPE
			SYNTAX Uint11
			MAX-ACCESS read-write
			STATUS current
			DESCRIPTION
				"Allows adjust of logo vertical position"
		::= { hli3000c01v1Entry 43 }

		-- 1.3.6.1.4.1.10106.3.101291.1.1.45
		hli3000c01v1PosHLogo4 OBJECT-TYPE
			SYNTAX Uint11
			MAX-ACCESS read-write
			STATUS current
			DESCRIPTION
				"Allows adjust of logo horizontal position"
		::= { hli3000c01v1Entry 45 }

		-- 1.3.6.1.4.1.10106.3.101291.1.1.47
		hli3000c01v1PosVLogo4 OBJECT-TYPE
			SYNTAX Uint11
			MAX-ACCESS read-write
			STATUS current
			DESCRIPTION
				"Allows adjust of logo vertical position"
		::= { hli3000c01v1Entry 47 }

		-- 1.3.6.1.4.1.10106.3.101291.1.1.49
		hli3000c01v1InputFPresSel OBJECT-TYPE
			SYNTAX Preset16Default
			MAX-ACCESS read-write
			STATUS current
			DESCRIPTION
				"Preset loaded when input fails"
		::= { hli3000c01v1Entry 49 }

		-- 1.3.6.1.4.1.10106.3.101291.1.1.51
		hli3000c01v1NoSignal OBJECT-TYPE
			SYNTAX BitFail
			MAX-ACCESS read-only
			STATUS current
			DESCRIPTION
				"There is no SDI signal or the format is not supported"
		::= { hli3000c01v1Entry 51 }

		-- 1.3.6.1.4.1.10106.3.101291.1.1.52
		hli3000c01v1NoSignalTrapEnable OBJECT-TYPE
			SYNTAX AlarmEnable
			MAX-ACCESS read-write
			STATUS current
			DESCRIPTION
				"There is no SDI signal or the format is not supported Trap Enable"
		::= { hli3000c01v1Entry 52 }

		-- 1.3.6.1.4.1.10106.3.101291.1.1.53
		hli3000c01v1Unlock OBJECT-TYPE
			SYNTAX BitFail
			MAX-ACCESS read-only
			STATUS current
			DESCRIPTION
				"Indicates signal unlock fail"
		::= { hli3000c01v1Entry 53 }

		-- 1.3.6.1.4.1.10106.3.101291.1.1.54
		hli3000c01v1UnlockTrapEnable OBJECT-TYPE
			SYNTAX AlarmEnable
			MAX-ACCESS read-write
			STATUS current
			DESCRIPTION
				"Indicates signal unlock fail Trap Enable"
		::= { hli3000c01v1Entry 54 }

		-- 1.3.6.1.4.1.10106.3.101291.1.1.55
		hli3000c01v1EdhError OBJECT-TYPE
			SYNTAX BitFail
			MAX-ACCESS read-only
			STATUS current
			DESCRIPTION
				"There are EDH/CRC errors on SDI signal"
		::= { hli3000c01v1Entry 55 }

		-- 1.3.6.1.4.1.10106.3.101291.1.1.56
		hli3000c01v1EdhErrorTrapEnable OBJECT-TYPE
			SYNTAX AlarmEnable
			MAX-ACCESS read-write
			STATUS current
			DESCRIPTION
				"There are EDH/CRC errors on SDI signal Trap Enable"
		::= { hli3000c01v1Entry 56 }

		-- 1.3.6.1.4.1.10106.3.101291.1.1.57
		hli3000c01v1Format OBJECT-TYPE
			SYNTAX SdiHd3gFmt3
			MAX-ACCESS read-only
			STATUS current
			DESCRIPTION
				"Indicates the SDI received signal format"
		::= { hli3000c01v1Entry 57 }

		-- 1.3.6.1.4.1.10106.3.101291.1.1.58
		hli3000c01v1FormatTrapEnable OBJECT-TYPE
			SYNTAX AlarmEnable
			MAX-ACCESS read-write
			STATUS current
			DESCRIPTION
				"Indicates the SDI received signal format Trap Enable"
		::= { hli3000c01v1Entry 58 }

		-- 1.3.6.1.4.1.10106.3.101291.1.1.59
		hli3000c01v1Gpi1 OBJECT-TYPE
			SYNTAX Bit0Off1On
			MAX-ACCESS read-only
			STATUS current
			DESCRIPTION
				"Transmitted GPI1"
		::= { hli3000c01v1Entry 59 }

		-- 1.3.6.1.4.1.10106.3.101291.1.1.60
		hli3000c01v1Gpi1TrapEnable OBJECT-TYPE
			SYNTAX AlarmEnable
			MAX-ACCESS read-write
			STATUS current
			DESCRIPTION
				"Transmitted GPI1 Trap Enable"
		::= { hli3000c01v1Entry 60 }

		-- 1.3.6.1.4.1.10106.3.101291.1.1.61
		hli3000c01v1Gpi2 OBJECT-TYPE
			SYNTAX Bit0Off1On
			MAX-ACCESS read-only
			STATUS current
			DESCRIPTION
				"Transmitted GPI2"
		::= { hli3000c01v1Entry 61 }

		-- 1.3.6.1.4.1.10106.3.101291.1.1.62
		hli3000c01v1Gpi2TrapEnable OBJECT-TYPE
			SYNTAX AlarmEnable
			MAX-ACCESS read-write
			STATUS current
			DESCRIPTION
				"Transmitted GPI2 Trap Enable"
		::= { hli3000c01v1Entry 62 }

		-- 1.3.6.1.4.1.10106.3.101291.1.1.63
		hli3000c01v1Gpi3 OBJECT-TYPE
			SYNTAX Bit0Off1On
			MAX-ACCESS read-only
			STATUS current
			DESCRIPTION
				"Transmitted GPI3"
		::= { hli3000c01v1Entry 63 }

		-- 1.3.6.1.4.1.10106.3.101291.1.1.64
		hli3000c01v1Gpi3TrapEnable OBJECT-TYPE
			SYNTAX AlarmEnable
			MAX-ACCESS read-write
			STATUS current
			DESCRIPTION
				"Transmitted GPI3 Trap Enable"
		::= { hli3000c01v1Entry 64 }

		-- 1.3.6.1.4.1.10106.3.101291.1.1.65
		hli3000c01v1Gpi4 OBJECT-TYPE
			SYNTAX Bit0Off1On
			MAX-ACCESS read-only
			STATUS current
			DESCRIPTION
				"Transmitted GPI4"
		::= { hli3000c01v1Entry 65 }

		-- 1.3.6.1.4.1.10106.3.101291.1.1.66
		hli3000c01v1Gpi4TrapEnable OBJECT-TYPE
			SYNTAX AlarmEnable
			MAX-ACCESS read-write
			STATUS current
			DESCRIPTION
				"Transmitted GPI4 Trap Enable"
		::= { hli3000c01v1Entry 66 }

		-- 1.3.6.1.4.1.10106.3.101291.1.1.67
		hli3000c01v1Gpi5 OBJECT-TYPE
			SYNTAX Bit0Off1On
			MAX-ACCESS read-only
			STATUS current
			DESCRIPTION
				"Transmitted GPI5"
		::= { hli3000c01v1Entry 67 }

		-- 1.3.6.1.4.1.10106.3.101291.1.1.68
		hli3000c01v1Gpi5TrapEnable OBJECT-TYPE
			SYNTAX AlarmEnable
			MAX-ACCESS read-write
			STATUS current
			DESCRIPTION
				"Transmitted GPI5 Trap Enable"
		::= { hli3000c01v1Entry 68 }

		-- 1.3.6.1.4.1.10106.3.101291.1.1.69
		hli3000c01v1Gpi6 OBJECT-TYPE
			SYNTAX Bit0Off1On
			MAX-ACCESS read-only
			STATUS current
			DESCRIPTION
				"Transmitted GPI6"
		::= { hli3000c01v1Entry 69 }

		-- 1.3.6.1.4.1.10106.3.101291.1.1.70
		hli3000c01v1Gpi6TrapEnable OBJECT-TYPE
			SYNTAX AlarmEnable
			MAX-ACCESS read-write
			STATUS current
			DESCRIPTION
				"Transmitted GPI6 Trap Enable"
		::= { hli3000c01v1Entry 70 }

		-- 1.3.6.1.4.1.10106.3.101291.1.1.71
		hli3000c01v1Gpi7 OBJECT-TYPE
			SYNTAX Bit0Off1On
			MAX-ACCESS read-only
			STATUS current
			DESCRIPTION
				"Transmitted GPI7"
		::= { hli3000c01v1Entry 71 }

		-- 1.3.6.1.4.1.10106.3.101291.1.1.72
		hli3000c01v1Gpi7TrapEnable OBJECT-TYPE
			SYNTAX AlarmEnable
			MAX-ACCESS read-write
			STATUS current
			DESCRIPTION
				"Transmitted GPI7 Trap Enable"
		::= { hli3000c01v1Entry 72 }

		-- 1.3.6.1.4.1.10106.3.101291.1.1.73
		hli3000c01v1Gpi8 OBJECT-TYPE
			SYNTAX Bit0Off1On
			MAX-ACCESS read-only
			STATUS current
			DESCRIPTION
				"Transmitted GPI8"
		::= { hli3000c01v1Entry 73 }

		-- 1.3.6.1.4.1.10106.3.101291.1.1.74
		hli3000c01v1Gpi8TrapEnable OBJECT-TYPE
			SYNTAX AlarmEnable
			MAX-ACCESS read-write
			STATUS current
			DESCRIPTION
				"Transmitted GPI8 Trap Enable"
		::= { hli3000c01v1Entry 74 }

		-- 1.3.6.1.4.1.10106.3.101291.1.1.75
		hli3000c01v1LdLogo1Stat OBJECT-TYPE
			SYNTAX HliLdStat
			MAX-ACCESS read-only
			STATUS current
			DESCRIPTION
				"Logo status"
		::= { hli3000c01v1Entry 75 }

		-- 1.3.6.1.4.1.10106.3.101291.1.1.77
		hli3000c01v1LdLogo2Stat OBJECT-TYPE
			SYNTAX HliLdStat
			MAX-ACCESS read-only
			STATUS current
			DESCRIPTION
				"Logo status"
		::= { hli3000c01v1Entry 77 }

		-- 1.3.6.1.4.1.10106.3.101291.1.1.79
		hli3000c01v1LdLogo3Stat OBJECT-TYPE
			SYNTAX HliLdStat
			MAX-ACCESS read-only
			STATUS current
			DESCRIPTION
				"Logo status"
		::= { hli3000c01v1Entry 79 }

		-- 1.3.6.1.4.1.10106.3.101291.1.1.81
		hli3000c01v1LdLogo4Stat OBJECT-TYPE
			SYNTAX HliLdStat
			MAX-ACCESS read-only
			STATUS current
			DESCRIPTION
				"Logo status"
		::= { hli3000c01v1Entry 81 }

		-- 1.3.6.1.4.1.10106.3.101291.1.1.83
		hli3000c01v1SerialNo OBJECT-TYPE
			SYNTAX SerialNo
			MAX-ACCESS read-only
			STATUS current
			DESCRIPTION
				"Serial number"
		::= { hli3000c01v1Entry 83 }

		-- 1.3.6.1.4.1.10106.3.379802
		hli3000c01v2 OBJECT IDENTIFIER ::= { albalaProducts 379802 }

		-- 1.3.6.1.4.1.10106.3.379802.1
		hli3000c01v2Table  OBJECT-TYPE
			SYNTAX SEQUENCE OF Hli3000c01v2Entry
			MAX-ACCESS not-accessible
			STATUS current
			DESCRIPTION
				"Module  HLI3000C01V2 Table"
			::= { hli3000c01v2 1 }

		-- 1.3.6.1.4.1.10106.3.379802.1.1
		hli3000c01v2Entry  OBJECT-TYPE
			SYNTAX Hli3000c01v2Entry
			MAX-ACCESS not-accessible
			STATUS current
			DESCRIPTION
				"Module HLI3000C01V2 Entry"
			INDEX { hli3000c01v2Index }
			::= { hli3000c01v2Table 1 }

			Hli3000c01v2Entry ::=
			SEQUENCE {
				hli3000c01v2Index
				ModuleIndex,
				hli3000c01v2ActivePreset
				Preset16Active,
				hli3000c01v2ActivePresetTrapEnable
				AlarmEnable,
				hli3000c01v2LoadPreset
				Preset16Load,
				hli3000c01v2SavePreset
				Preset16Save,
				hli3000c01v2PgmInsLogo1
				Bit0No1Yes,
				hli3000c01v2PgmInsLogo1TrapEnable
				AlarmEnable,
				hli3000c01v2PgmInsLogo2
				Bit0No1Yes,
				hli3000c01v2PgmInsLogo2TrapEnable
				AlarmEnable,
				hli3000c01v2PgmInsLogo3
				Bit0No1Yes,
				hli3000c01v2PgmInsLogo3TrapEnable
				AlarmEnable,
				hli3000c01v2PgmInsLogo4
				Bit0No1Yes,
				hli3000c01v2PgmInsLogo4TrapEnable
				AlarmEnable,
				hli3000c01v2PvwInsLogo1
				Bit0No1Yes,
				hli3000c01v2PvwInsLogo2
				Bit0No1Yes,
				hli3000c01v2PvwInsLogo3
				Bit0No1Yes,
				hli3000c01v2PvwInsLogo4
				Bit0No1Yes,
				hli3000c01v2ClockSource
				TcSource,
				hli3000c01v2PgmInsClock
				Bit0No1Yes,
				hli3000c01v2PvwInsClock
				Bit0No1Yes,
				hli3000c01v2ClockPosition
				ClockPosition,
				hli3000c01v2SelLogo1
				Uint8,
				hli3000c01v2SelLogo1TrapEnable
				AlarmEnable,
				hli3000c01v2SelLogo2
				Uint8,
				hli3000c01v2SelLogo2TrapEnable
				AlarmEnable,
				hli3000c01v2SelLogo3
				Uint8,
				hli3000c01v2SelLogo3TrapEnable
				AlarmEnable,
				hli3000c01v2SelLogo4
				Uint8,
				hli3000c01v2SelLogo4TrapEnable
				AlarmEnable,
				hli3000c01v2PosHLogo1
				Uint11,
				hli3000c01v2PosVLogo1
				Uint11,
				hli3000c01v2PosHLogo2
				Uint11,
				hli3000c01v2PosVLogo2
				Uint11,
				hli3000c01v2PosHLogo3
				Uint11,
				hli3000c01v2PosVLogo3
				Uint11,
				hli3000c01v2PosHLogo4
				Uint11,
				hli3000c01v2PosVLogo4
				Uint11,
				hli3000c01v2EnaMovLogo1
				Bit0No1Yes,
				hli3000c01v2EnaMovLogo2
				Bit0No1Yes,
				hli3000c01v2EnaMovLogo3
				Bit0No1Yes,
				hli3000c01v2EnaMovLogo4
				Bit0No1Yes,
				hli3000c01v2MovLogoSpeed
				Uint4,
				hli3000c01v2MovLogoIncX
				Uint11,
				hli3000c01v2MovLogoIncY
				Uint11,
				hli3000c01v2CrawlEnLogo1
				Bit0No1Yes,
				hli3000c01v2CrawlEnLogo2
				Bit0No1Yes,
				hli3000c01v2CrawlEnLogo3
				Bit0No1Yes,
				hli3000c01v2CrawlEnLogo4
				Bit0No1Yes,
				hli3000c01v2CrwlContLogo1
				Bit0No1Yes,
				hli3000c01v2CrwlContLogo2
				Bit0No1Yes,
				hli3000c01v2CrwlContLogo3
				Bit0No1Yes,
				hli3000c01v2CrwlContLogo4
				Bit0No1Yes,
				hli3000c01v2InputFPresSel
				Preset16Default,
				hli3000c01v2ClockFormat
				ClockFormat,
				hli3000c01v2ClockAmPm
				ClockAmPm,
				hli3000c01v2ClockSize
				ClockSize,
				hli3000c01v2CrawlSpeed
				Uint4,
				hli3000c01v2CrawlTimeS
				TimeS1,
				hli3000c01v2CrawlTimeM
				TimeM1,
				hli3000c01v2CrawlTimeH
				TimeH1,
				hli3000c01v2NoSignal
				BitFail,
				hli3000c01v2NoSignalTrapEnable
				AlarmEnable,
				hli3000c01v2Unlock
				BitFail,
				hli3000c01v2UnlockTrapEnable
				AlarmEnable,
				hli3000c01v2EdhError
				BitFail,
				hli3000c01v2EdhErrorTrapEnable
				AlarmEnable,
				hli3000c01v2Format
				SdiHd3gFmt3,
				hli3000c01v2FormatTrapEnable
				AlarmEnable,
				hli3000c01v2Gpi1
				Bit0Off1On,
				hli3000c01v2Gpi1TrapEnable
				AlarmEnable,
				hli3000c01v2Gpi2
				Bit0Off1On,
				hli3000c01v2Gpi2TrapEnable
				AlarmEnable,
				hli3000c01v2Gpi3
				Bit0Off1On,
				hli3000c01v2Gpi3TrapEnable
				AlarmEnable,
				hli3000c01v2Gpi4
				Bit0Off1On,
				hli3000c01v2Gpi4TrapEnable
				AlarmEnable,
				hli3000c01v2Gpi5
				Bit0Off1On,
				hli3000c01v2Gpi5TrapEnable
				AlarmEnable,
				hli3000c01v2Gpi6
				Bit0Off1On,
				hli3000c01v2Gpi6TrapEnable
				AlarmEnable,
				hli3000c01v2Gpi7
				Bit0Off1On,
				hli3000c01v2Gpi7TrapEnable
				AlarmEnable,
				hli3000c01v2Gpi8
				Bit0Off1On,
				hli3000c01v2Gpi8TrapEnable
				AlarmEnable,
				hli3000c01v2LdLogo1Stat
				HliLdStat,
				hli3000c01v2LdLogo2Stat
				HliLdStat,
				hli3000c01v2LdLogo3Stat
				HliLdStat,
				hli3000c01v2LdLogo4Stat
				HliLdStat,
				hli3000c01v2SerialNo
				SerialNo
			 }

		-- 1.3.6.1.4.1.10106.3.101291.1.1.1
		hli3000c01v2Index OBJECT-TYPE
			SYNTAX ModuleIndex
			MAX-ACCESS read-only
			STATUS current
			DESCRIPTION
				"Index of HLI3000C01V2 Table"
		::= { hli3000c01v2Entry 1 }

		-- 1.3.6.1.4.1.10106.3.101291.1.1.3
		hli3000c01v2ActivePreset OBJECT-TYPE
			SYNTAX Preset16Active
			MAX-ACCESS read-only
			STATUS current
			DESCRIPTION
				"Shows the active preset"
		::= { hli3000c01v2Entry 3 }

		-- 1.3.6.1.4.1.10106.3.101291.1.1.4
		hli3000c01v2ActivePresetTrapEnable OBJECT-TYPE
			SYNTAX AlarmEnable
			MAX-ACCESS read-write
			STATUS current
			DESCRIPTION
				"Shows the active preset Trap Enable"
		::= { hli3000c01v2Entry 4 }

		-- 1.3.6.1.4.1.10106.3.101291.1.1.5
		hli3000c01v2LoadPreset OBJECT-TYPE
			SYNTAX Preset16Load
			MAX-ACCESS read-write
			STATUS current
			DESCRIPTION
				"Allows loading a preset"
		::= { hli3000c01v2Entry 5 }

		-- 1.3.6.1.4.1.10106.3.101291.1.1.7
		hli3000c01v2SavePreset OBJECT-TYPE
			SYNTAX Preset16Save
			MAX-ACCESS read-write
			STATUS current
			DESCRIPTION
				"Allows saving a preset"
		::= { hli3000c01v2Entry 7 }

		-- 1.3.6.1.4.1.10106.3.101291.1.1.9
		hli3000c01v2PgmInsLogo1 OBJECT-TYPE
			SYNTAX Bit0No1Yes
			MAX-ACCESS read-write
			STATUS current
			DESCRIPTION
				"Allows inserting the logo in the program output"
		::= { hli3000c01v2Entry 9 }

		-- 1.3.6.1.4.1.10106.3.101291.1.1.10
		hli3000c01v2PgmInsLogo1TrapEnable OBJECT-TYPE
			SYNTAX AlarmEnable
			MAX-ACCESS read-write
			STATUS current
			DESCRIPTION
				"Allows inserting the logo in the program output Trap Enable"
		::= { hli3000c01v2Entry 10 }

		-- 1.3.6.1.4.1.10106.3.101291.1.1.11
		hli3000c01v2PgmInsLogo2 OBJECT-TYPE
			SYNTAX Bit0No1Yes
			MAX-ACCESS read-write
			STATUS current
			DESCRIPTION
				"Allows inserting the logo in the program output"
		::= { hli3000c01v2Entry 11 }

		-- 1.3.6.1.4.1.10106.3.101291.1.1.12
		hli3000c01v2PgmInsLogo2TrapEnable OBJECT-TYPE
			SYNTAX AlarmEnable
			MAX-ACCESS read-write
			STATUS current
			DESCRIPTION
				"Allows inserting the logo in the program output Trap Enable"
		::= { hli3000c01v2Entry 12 }

		-- 1.3.6.1.4.1.10106.3.101291.1.1.13
		hli3000c01v2PgmInsLogo3 OBJECT-TYPE
			SYNTAX Bit0No1Yes
			MAX-ACCESS read-write
			STATUS current
			DESCRIPTION
				"Allows inserting the logo in the program output"
		::= { hli3000c01v2Entry 13 }

		-- 1.3.6.1.4.1.10106.3.101291.1.1.14
		hli3000c01v2PgmInsLogo3TrapEnable OBJECT-TYPE
			SYNTAX AlarmEnable
			MAX-ACCESS read-write
			STATUS current
			DESCRIPTION
				"Allows inserting the logo in the program output Trap Enable"
		::= { hli3000c01v2Entry 14 }

		-- 1.3.6.1.4.1.10106.3.101291.1.1.15
		hli3000c01v2PgmInsLogo4 OBJECT-TYPE
			SYNTAX Bit0No1Yes
			MAX-ACCESS read-write
			STATUS current
			DESCRIPTION
				"Allows inserting the logo in the program output"
		::= { hli3000c01v2Entry 15 }

		-- 1.3.6.1.4.1.10106.3.101291.1.1.16
		hli3000c01v2PgmInsLogo4TrapEnable OBJECT-TYPE
			SYNTAX AlarmEnable
			MAX-ACCESS read-write
			STATUS current
			DESCRIPTION
				"Allows inserting the logo in the program output Trap Enable"
		::= { hli3000c01v2Entry 16 }

		-- 1.3.6.1.4.1.10106.3.101291.1.1.17
		hli3000c01v2PvwInsLogo1 OBJECT-TYPE
			SYNTAX Bit0No1Yes
			MAX-ACCESS read-write
			STATUS current
			DESCRIPTION
				"Allows inserting the logo in the preview output"
		::= { hli3000c01v2Entry 17 }

		-- 1.3.6.1.4.1.10106.3.101291.1.1.19
		hli3000c01v2PvwInsLogo2 OBJECT-TYPE
			SYNTAX Bit0No1Yes
			MAX-ACCESS read-write
			STATUS current
			DESCRIPTION
				"Allows inserting the logo in the preview output"
		::= { hli3000c01v2Entry 19 }

		-- 1.3.6.1.4.1.10106.3.101291.1.1.21
		hli3000c01v2PvwInsLogo3 OBJECT-TYPE
			SYNTAX Bit0No1Yes
			MAX-ACCESS read-write
			STATUS current
			DESCRIPTION
				"Allows inserting the logo in the preview output"
		::= { hli3000c01v2Entry 21 }

		-- 1.3.6.1.4.1.10106.3.101291.1.1.23
		hli3000c01v2PvwInsLogo4 OBJECT-TYPE
			SYNTAX Bit0No1Yes
			MAX-ACCESS read-write
			STATUS current
			DESCRIPTION
				"Allows inserting the logo in the preview output"
		::= { hli3000c01v2Entry 23 }

		-- 1.3.6.1.4.1.10106.3.101291.1.1.25
		hli3000c01v2ClockSource OBJECT-TYPE
			SYNTAX TcSource
			MAX-ACCESS read-write
			STATUS current
			DESCRIPTION
				"selecting TC source used for clock"
		::= { hli3000c01v2Entry 25 }

		-- 1.3.6.1.4.1.10106.3.101291.1.1.27
		hli3000c01v2PgmInsClock OBJECT-TYPE
			SYNTAX Bit0No1Yes
			MAX-ACCESS read-write
			STATUS current
			DESCRIPTION
				"Allows inserting the clock in the program output"
		::= { hli3000c01v2Entry 27 }

		-- 1.3.6.1.4.1.10106.3.101291.1.1.29
		hli3000c01v2PvwInsClock OBJECT-TYPE
			SYNTAX Bit0No1Yes
			MAX-ACCESS read-write
			STATUS current
			DESCRIPTION
				"Allows inserting the clock in the preview output"
		::= { hli3000c01v2Entry 29 }

		-- 1.3.6.1.4.1.10106.3.101291.1.1.31
		hli3000c01v2ClockPosition OBJECT-TYPE
			SYNTAX ClockPosition
			MAX-ACCESS read-write
			STATUS current
			DESCRIPTION
				"Allows selecting the clock position in screen"
		::= { hli3000c01v2Entry 31 }

		-- 1.3.6.1.4.1.10106.3.101291.1.1.33
		hli3000c01v2SelLogo1 OBJECT-TYPE
			SYNTAX Uint8
			MAX-ACCESS read-write
			STATUS current
			DESCRIPTION
				"Allows selecting the logo to be inserted"
		::= { hli3000c01v2Entry 33 }

		-- 1.3.6.1.4.1.10106.3.101291.1.1.34
		hli3000c01v2SelLogo1TrapEnable OBJECT-TYPE
			SYNTAX AlarmEnable
			MAX-ACCESS read-write
			STATUS current
			DESCRIPTION
				"Allows selecting the logo to be inserted Trap Enable"
		::= { hli3000c01v2Entry 34 }

		-- 1.3.6.1.4.1.10106.3.101291.1.1.35
		hli3000c01v2SelLogo2 OBJECT-TYPE
			SYNTAX Uint8
			MAX-ACCESS read-write
			STATUS current
			DESCRIPTION
				"Allows selecting the logo to be inserted"
		::= { hli3000c01v2Entry 35 }

		-- 1.3.6.1.4.1.10106.3.101291.1.1.36
		hli3000c01v2SelLogo2TrapEnable OBJECT-TYPE
			SYNTAX AlarmEnable
			MAX-ACCESS read-write
			STATUS current
			DESCRIPTION
				"Allows selecting the logo to be inserted Trap Enable"
		::= { hli3000c01v2Entry 36 }

		-- 1.3.6.1.4.1.10106.3.101291.1.1.37
		hli3000c01v2SelLogo3 OBJECT-TYPE
			SYNTAX Uint8
			MAX-ACCESS read-write
			STATUS current
			DESCRIPTION
				"Allows selecting the logo to be inserted"
		::= { hli3000c01v2Entry 37 }

		-- 1.3.6.1.4.1.10106.3.101291.1.1.38
		hli3000c01v2SelLogo3TrapEnable OBJECT-TYPE
			SYNTAX AlarmEnable
			MAX-ACCESS read-write
			STATUS current
			DESCRIPTION
				"Allows selecting the logo to be inserted Trap Enable"
		::= { hli3000c01v2Entry 38 }

		-- 1.3.6.1.4.1.10106.3.101291.1.1.39
		hli3000c01v2SelLogo4 OBJECT-TYPE
			SYNTAX Uint8
			MAX-ACCESS read-write
			STATUS current
			DESCRIPTION
				"Allows selecting the logo to be inserted"
		::= { hli3000c01v2Entry 39 }

		-- 1.3.6.1.4.1.10106.3.101291.1.1.40
		hli3000c01v2SelLogo4TrapEnable OBJECT-TYPE
			SYNTAX AlarmEnable
			MAX-ACCESS read-write
			STATUS current
			DESCRIPTION
				"Allows selecting the logo to be inserted Trap Enable"
		::= { hli3000c01v2Entry 40 }

		-- 1.3.6.1.4.1.10106.3.101291.1.1.41
		hli3000c01v2PosHLogo1 OBJECT-TYPE
			SYNTAX Uint11
			MAX-ACCESS read-write
			STATUS current
			DESCRIPTION
				"Allows adjust of logo horizontal position"
		::= { hli3000c01v2Entry 41 }

		-- 1.3.6.1.4.1.10106.3.101291.1.1.43
		hli3000c01v2PosVLogo1 OBJECT-TYPE
			SYNTAX Uint11
			MAX-ACCESS read-write
			STATUS current
			DESCRIPTION
				"Allows adjust of logo vertical position"
		::= { hli3000c01v2Entry 43 }

		-- 1.3.6.1.4.1.10106.3.101291.1.1.45
		hli3000c01v2PosHLogo2 OBJECT-TYPE
			SYNTAX Uint11
			MAX-ACCESS read-write
			STATUS current
			DESCRIPTION
				"Allows adjust of logo horizontal position"
		::= { hli3000c01v2Entry 45 }

		-- 1.3.6.1.4.1.10106.3.101291.1.1.47
		hli3000c01v2PosVLogo2 OBJECT-TYPE
			SYNTAX Uint11
			MAX-ACCESS read-write
			STATUS current
			DESCRIPTION
				"Allows adjust of logo vertical position"
		::= { hli3000c01v2Entry 47 }

		-- 1.3.6.1.4.1.10106.3.101291.1.1.49
		hli3000c01v2PosHLogo3 OBJECT-TYPE
			SYNTAX Uint11
			MAX-ACCESS read-write
			STATUS current
			DESCRIPTION
				"Allows adjust of logo horizontal position"
		::= { hli3000c01v2Entry 49 }

		-- 1.3.6.1.4.1.10106.3.101291.1.1.51
		hli3000c01v2PosVLogo3 OBJECT-TYPE
			SYNTAX Uint11
			MAX-ACCESS read-write
			STATUS current
			DESCRIPTION
				"Allows adjust of logo vertical position"
		::= { hli3000c01v2Entry 51 }

		-- 1.3.6.1.4.1.10106.3.101291.1.1.53
		hli3000c01v2PosHLogo4 OBJECT-TYPE
			SYNTAX Uint11
			MAX-ACCESS read-write
			STATUS current
			DESCRIPTION
				"Allows adjust of logo horizontal position"
		::= { hli3000c01v2Entry 53 }

		-- 1.3.6.1.4.1.10106.3.101291.1.1.55
		hli3000c01v2PosVLogo4 OBJECT-TYPE
			SYNTAX Uint11
			MAX-ACCESS read-write
			STATUS current
			DESCRIPTION
				"Allows adjust of logo vertical position"
		::= { hli3000c01v2Entry 55 }

		-- 1.3.6.1.4.1.10106.3.101291.1.1.57
		hli3000c01v2EnaMovLogo1 OBJECT-TYPE
			SYNTAX Bit0No1Yes
			MAX-ACCESS read-write
			STATUS current
			DESCRIPTION
				"Allows enabling moving logo"
		::= { hli3000c01v2Entry 57 }

		-- 1.3.6.1.4.1.10106.3.101291.1.1.59
		hli3000c01v2EnaMovLogo2 OBJECT-TYPE
			SYNTAX Bit0No1Yes
			MAX-ACCESS read-write
			STATUS current
			DESCRIPTION
				"Allows enabling moving logo"
		::= { hli3000c01v2Entry 59 }

		-- 1.3.6.1.4.1.10106.3.101291.1.1.61
		hli3000c01v2EnaMovLogo3 OBJECT-TYPE
			SYNTAX Bit0No1Yes
			MAX-ACCESS read-write
			STATUS current
			DESCRIPTION
				"Allows enabling moving logo"
		::= { hli3000c01v2Entry 61 }

		-- 1.3.6.1.4.1.10106.3.101291.1.1.63
		hli3000c01v2EnaMovLogo4 OBJECT-TYPE
			SYNTAX Bit0No1Yes
			MAX-ACCESS read-write
			STATUS current
			DESCRIPTION
				"Allows enabling moving logo"
		::= { hli3000c01v2Entry 63 }

		-- 1.3.6.1.4.1.10106.3.101291.1.1.65
		hli3000c01v2MovLogoSpeed OBJECT-TYPE
			SYNTAX Uint4
			MAX-ACCESS read-write
			STATUS current
			DESCRIPTION
				"Allows selecting the logo moving speed"
		::= { hli3000c01v2Entry 65 }

		-- 1.3.6.1.4.1.10106.3.101291.1.1.67
		hli3000c01v2MovLogoIncX OBJECT-TYPE
			SYNTAX Uint11
			MAX-ACCESS read-write
			STATUS current
			DESCRIPTION
				"Allows selecting the moving window x coordinate"
		::= { hli3000c01v2Entry 67 }

		-- 1.3.6.1.4.1.10106.3.101291.1.1.69
		hli3000c01v2MovLogoIncY OBJECT-TYPE
			SYNTAX Uint11
			MAX-ACCESS read-write
			STATUS current
			DESCRIPTION
				"Allows selecting the moving window y coordinate"
		::= { hli3000c01v2Entry 69 }

		-- 1.3.6.1.4.1.10106.3.101291.1.1.71
		hli3000c01v2CrawlEnLogo1 OBJECT-TYPE
			SYNTAX Bit0No1Yes
			MAX-ACCESS read-write
			STATUS current
			DESCRIPTION
				"Allows enabling crawl on logo 1"
		::= { hli3000c01v2Entry 71 }

		-- 1.3.6.1.4.1.10106.3.101291.1.1.73
		hli3000c01v2CrawlEnLogo2 OBJECT-TYPE
			SYNTAX Bit0No1Yes
			MAX-ACCESS read-write
			STATUS current
			DESCRIPTION
				"Allows enabling crawl on logo 2"
		::= { hli3000c01v2Entry 73 }

		-- 1.3.6.1.4.1.10106.3.101291.1.1.75
		hli3000c01v2CrawlEnLogo3 OBJECT-TYPE
			SYNTAX Bit0No1Yes
			MAX-ACCESS read-write
			STATUS current
			DESCRIPTION
				"Allows enabling crawl on logo 3"
		::= { hli3000c01v2Entry 75 }

		-- 1.3.6.1.4.1.10106.3.101291.1.1.77
		hli3000c01v2CrawlEnLogo4 OBJECT-TYPE
			SYNTAX Bit0No1Yes
			MAX-ACCESS read-write
			STATUS current
			DESCRIPTION
				"Allows enabling crawl on logo 4"
		::= { hli3000c01v2Entry 77 }

		-- 1.3.6.1.4.1.10106.3.101291.1.1.79
		hli3000c01v2CrwlContLogo1 OBJECT-TYPE
			SYNTAX Bit0No1Yes
			MAX-ACCESS read-write
			STATUS current
			DESCRIPTION
				"Allows enabling continous crawl"
		::= { hli3000c01v2Entry 79 }

		-- 1.3.6.1.4.1.10106.3.101291.1.1.81
		hli3000c01v2CrwlContLogo2 OBJECT-TYPE
			SYNTAX Bit0No1Yes
			MAX-ACCESS read-write
			STATUS current
			DESCRIPTION
				"Allow linking logo 1 and logo 2 in crawl mode"
		::= { hli3000c01v2Entry 81 }

		-- 1.3.6.1.4.1.10106.3.101291.1.1.83
		hli3000c01v2CrwlContLogo3 OBJECT-TYPE
			SYNTAX Bit0No1Yes
			MAX-ACCESS read-write
			STATUS current
			DESCRIPTION
				"Allow linking logo 2 and logo 3 in crawl mode"
		::= { hli3000c01v2Entry 83 }

		-- 1.3.6.1.4.1.10106.3.101291.1.1.85
		hli3000c01v2CrwlContLogo4 OBJECT-TYPE
			SYNTAX Bit0No1Yes
			MAX-ACCESS read-write
			STATUS current
			DESCRIPTION
				"Allow linking logo 3 and logo 4 in crawl mode"
		::= { hli3000c01v2Entry 85 }

		-- 1.3.6.1.4.1.10106.3.101291.1.1.87
		hli3000c01v2InputFPresSel OBJECT-TYPE
			SYNTAX Preset16Default
			MAX-ACCESS read-write
			STATUS current
			DESCRIPTION
				"Preset loaded when input fails"
		::= { hli3000c01v2Entry 87 }

		-- 1.3.6.1.4.1.10106.3.101291.1.1.89
		hli3000c01v2ClockFormat OBJECT-TYPE
			SYNTAX ClockFormat
			MAX-ACCESS read-write
			STATUS current
			DESCRIPTION
				"Allows selectign the clock format"
		::= { hli3000c01v2Entry 89 }

		-- 1.3.6.1.4.1.10106.3.101291.1.1.91
		hli3000c01v2ClockAmPm OBJECT-TYPE
			SYNTAX ClockAmPm
			MAX-ACCESS read-write
			STATUS current
			DESCRIPTION
				"Allows selecting the clock mode"
		::= { hli3000c01v2Entry 91 }

		-- 1.3.6.1.4.1.10106.3.101291.1.1.93
		hli3000c01v2ClockSize OBJECT-TYPE
			SYNTAX ClockSize
			MAX-ACCESS read-write
			STATUS current
			DESCRIPTION
				"Allows selecting the clock size"
		::= { hli3000c01v2Entry 93 }

		-- 1.3.6.1.4.1.10106.3.101291.1.1.95
		hli3000c01v2CrawlSpeed OBJECT-TYPE
			SYNTAX Uint4
			MAX-ACCESS read-write
			STATUS current
			DESCRIPTION
				"Allows adjusting the crawl speed"
		::= { hli3000c01v2Entry 95 }

		-- 1.3.6.1.4.1.10106.3.101291.1.1.97
		hli3000c01v2CrawlTimeS OBJECT-TYPE
			SYNTAX TimeS1
			MAX-ACCESS read-write
			STATUS current
			DESCRIPTION
				"Allows adjusting the crawl period (s)"
		::= { hli3000c01v2Entry 97 }

		-- 1.3.6.1.4.1.10106.3.101291.1.1.99
		hli3000c01v2CrawlTimeM OBJECT-TYPE
			SYNTAX TimeM1
			MAX-ACCESS read-write
			STATUS current
			DESCRIPTION
				"Allows adjusting the crawl period (m)"
		::= { hli3000c01v2Entry 99 }

		-- 1.3.6.1.4.1.10106.3.101291.1.1.101
		hli3000c01v2CrawlTimeH OBJECT-TYPE
			SYNTAX TimeH1
			MAX-ACCESS read-write
			STATUS current
			DESCRIPTION
				"Allows adjusting the crawl period (h)"
		::= { hli3000c01v2Entry 101 }

		-- 1.3.6.1.4.1.10106.3.101291.1.1.103
		hli3000c01v2NoSignal OBJECT-TYPE
			SYNTAX BitFail
			MAX-ACCESS read-only
			STATUS current
			DESCRIPTION
				"There is no SDI signal or the format is not supported"
		::= { hli3000c01v2Entry 103 }

		-- 1.3.6.1.4.1.10106.3.101291.1.1.104
		hli3000c01v2NoSignalTrapEnable OBJECT-TYPE
			SYNTAX AlarmEnable
			MAX-ACCESS read-write
			STATUS current
			DESCRIPTION
				"There is no SDI signal or the format is not supported Trap Enable"
		::= { hli3000c01v2Entry 104 }

		-- 1.3.6.1.4.1.10106.3.101291.1.1.105
		hli3000c01v2Unlock OBJECT-TYPE
			SYNTAX BitFail
			MAX-ACCESS read-only
			STATUS current
			DESCRIPTION
				"Indicates signal unlock fail"
		::= { hli3000c01v2Entry 105 }

		-- 1.3.6.1.4.1.10106.3.101291.1.1.106
		hli3000c01v2UnlockTrapEnable OBJECT-TYPE
			SYNTAX AlarmEnable
			MAX-ACCESS read-write
			STATUS current
			DESCRIPTION
				"Indicates signal unlock fail Trap Enable"
		::= { hli3000c01v2Entry 106 }

		-- 1.3.6.1.4.1.10106.3.101291.1.1.107
		hli3000c01v2EdhError OBJECT-TYPE
			SYNTAX BitFail
			MAX-ACCESS read-only
			STATUS current
			DESCRIPTION
				"There are EDH/CRC errors on SDI signal"
		::= { hli3000c01v2Entry 107 }

		-- 1.3.6.1.4.1.10106.3.101291.1.1.108
		hli3000c01v2EdhErrorTrapEnable OBJECT-TYPE
			SYNTAX AlarmEnable
			MAX-ACCESS read-write
			STATUS current
			DESCRIPTION
				"There are EDH/CRC errors on SDI signal Trap Enable"
		::= { hli3000c01v2Entry 108 }

		-- 1.3.6.1.4.1.10106.3.101291.1.1.109
		hli3000c01v2Format OBJECT-TYPE
			SYNTAX SdiHd3gFmt3
			MAX-ACCESS read-only
			STATUS current
			DESCRIPTION
				"Indicates the SDI received signal format"
		::= { hli3000c01v2Entry 109 }

		-- 1.3.6.1.4.1.10106.3.101291.1.1.110
		hli3000c01v2FormatTrapEnable OBJECT-TYPE
			SYNTAX AlarmEnable
			MAX-ACCESS read-write
			STATUS current
			DESCRIPTION
				"Indicates the SDI received signal format Trap Enable"
		::= { hli3000c01v2Entry 110 }

		-- 1.3.6.1.4.1.10106.3.101291.1.1.111
		hli3000c01v2Gpi1 OBJECT-TYPE
			SYNTAX Bit0Off1On
			MAX-ACCESS read-only
			STATUS current
			DESCRIPTION
				"Transmitted GPI1"
		::= { hli3000c01v2Entry 111 }

		-- 1.3.6.1.4.1.10106.3.101291.1.1.112
		hli3000c01v2Gpi1TrapEnable OBJECT-TYPE
			SYNTAX AlarmEnable
			MAX-ACCESS read-write
			STATUS current
			DESCRIPTION
				"Transmitted GPI1 Trap Enable"
		::= { hli3000c01v2Entry 112 }

		-- 1.3.6.1.4.1.10106.3.101291.1.1.113
		hli3000c01v2Gpi2 OBJECT-TYPE
			SYNTAX Bit0Off1On
			MAX-ACCESS read-only
			STATUS current
			DESCRIPTION
				"Transmitted GPI2"
		::= { hli3000c01v2Entry 113 }

		-- 1.3.6.1.4.1.10106.3.101291.1.1.114
		hli3000c01v2Gpi2TrapEnable OBJECT-TYPE
			SYNTAX AlarmEnable
			MAX-ACCESS read-write
			STATUS current
			DESCRIPTION
				"Transmitted GPI2 Trap Enable"
		::= { hli3000c01v2Entry 114 }

		-- 1.3.6.1.4.1.10106.3.101291.1.1.115
		hli3000c01v2Gpi3 OBJECT-TYPE
			SYNTAX Bit0Off1On
			MAX-ACCESS read-only
			STATUS current
			DESCRIPTION
				"Transmitted GPI3"
		::= { hli3000c01v2Entry 115 }

		-- 1.3.6.1.4.1.10106.3.101291.1.1.116
		hli3000c01v2Gpi3TrapEnable OBJECT-TYPE
			SYNTAX AlarmEnable
			MAX-ACCESS read-write
			STATUS current
			DESCRIPTION
				"Transmitted GPI3 Trap Enable"
		::= { hli3000c01v2Entry 116 }

		-- 1.3.6.1.4.1.10106.3.101291.1.1.117
		hli3000c01v2Gpi4 OBJECT-TYPE
			SYNTAX Bit0Off1On
			MAX-ACCESS read-only
			STATUS current
			DESCRIPTION
				"Transmitted GPI4"
		::= { hli3000c01v2Entry 117 }

		-- 1.3.6.1.4.1.10106.3.101291.1.1.118
		hli3000c01v2Gpi4TrapEnable OBJECT-TYPE
			SYNTAX AlarmEnable
			MAX-ACCESS read-write
			STATUS current
			DESCRIPTION
				"Transmitted GPI4 Trap Enable"
		::= { hli3000c01v2Entry 118 }

		-- 1.3.6.1.4.1.10106.3.101291.1.1.119
		hli3000c01v2Gpi5 OBJECT-TYPE
			SYNTAX Bit0Off1On
			MAX-ACCESS read-only
			STATUS current
			DESCRIPTION
				"Transmitted GPI5"
		::= { hli3000c01v2Entry 119 }

		-- 1.3.6.1.4.1.10106.3.101291.1.1.120
		hli3000c01v2Gpi5TrapEnable OBJECT-TYPE
			SYNTAX AlarmEnable
			MAX-ACCESS read-write
			STATUS current
			DESCRIPTION
				"Transmitted GPI5 Trap Enable"
		::= { hli3000c01v2Entry 120 }

		-- 1.3.6.1.4.1.10106.3.101291.1.1.121
		hli3000c01v2Gpi6 OBJECT-TYPE
			SYNTAX Bit0Off1On
			MAX-ACCESS read-only
			STATUS current
			DESCRIPTION
				"Transmitted GPI6"
		::= { hli3000c01v2Entry 121 }

		-- 1.3.6.1.4.1.10106.3.101291.1.1.122
		hli3000c01v2Gpi6TrapEnable OBJECT-TYPE
			SYNTAX AlarmEnable
			MAX-ACCESS read-write
			STATUS current
			DESCRIPTION
				"Transmitted GPI6 Trap Enable"
		::= { hli3000c01v2Entry 122 }

		-- 1.3.6.1.4.1.10106.3.101291.1.1.123
		hli3000c01v2Gpi7 OBJECT-TYPE
			SYNTAX Bit0Off1On
			MAX-ACCESS read-only
			STATUS current
			DESCRIPTION
				"Transmitted GPI7"
		::= { hli3000c01v2Entry 123 }

		-- 1.3.6.1.4.1.10106.3.101291.1.1.124
		hli3000c01v2Gpi7TrapEnable OBJECT-TYPE
			SYNTAX AlarmEnable
			MAX-ACCESS read-write
			STATUS current
			DESCRIPTION
				"Transmitted GPI7 Trap Enable"
		::= { hli3000c01v2Entry 124 }

		-- 1.3.6.1.4.1.10106.3.101291.1.1.125
		hli3000c01v2Gpi8 OBJECT-TYPE
			SYNTAX Bit0Off1On
			MAX-ACCESS read-only
			STATUS current
			DESCRIPTION
				"Transmitted GPI8"
		::= { hli3000c01v2Entry 125 }

		-- 1.3.6.1.4.1.10106.3.101291.1.1.126
		hli3000c01v2Gpi8TrapEnable OBJECT-TYPE
			SYNTAX AlarmEnable
			MAX-ACCESS read-write
			STATUS current
			DESCRIPTION
				"Transmitted GPI8 Trap Enable"
		::= { hli3000c01v2Entry 126 }

		-- 1.3.6.1.4.1.10106.3.101291.1.1.127
		hli3000c01v2LdLogo1Stat OBJECT-TYPE
			SYNTAX HliLdStat
			MAX-ACCESS read-only
			STATUS current
			DESCRIPTION
				"Logo status"
		::= { hli3000c01v2Entry 127 }

		-- 1.3.6.1.4.1.10106.3.101291.1.1.129
		hli3000c01v2LdLogo2Stat OBJECT-TYPE
			SYNTAX HliLdStat
			MAX-ACCESS read-only
			STATUS current
			DESCRIPTION
				"Logo status"
		::= { hli3000c01v2Entry 129 }

		-- 1.3.6.1.4.1.10106.3.101291.1.1.131
		hli3000c01v2LdLogo3Stat OBJECT-TYPE
			SYNTAX HliLdStat
			MAX-ACCESS read-only
			STATUS current
			DESCRIPTION
				"Logo status"
		::= { hli3000c01v2Entry 131 }

		-- 1.3.6.1.4.1.10106.3.101291.1.1.133
		hli3000c01v2LdLogo4Stat OBJECT-TYPE
			SYNTAX HliLdStat
			MAX-ACCESS read-only
			STATUS current
			DESCRIPTION
				"Logo status"
		::= { hli3000c01v2Entry 133 }

		-- 1.3.6.1.4.1.10106.3.101291.1.1.135
		hli3000c01v2SerialNo OBJECT-TYPE
			SYNTAX SerialNo
			MAX-ACCESS read-only
			STATUS current
			DESCRIPTION
				"Serial number"
		::= { hli3000c01v2Entry 135 }

		-- 1.3.6.1.4.1.10106.3.380001
		eop0010c01v1 OBJECT IDENTIFIER ::= { albalaProducts 380001 }

		-- 1.3.6.1.4.1.10106.3.380001.1
		eop0010c01v1Table  OBJECT-TYPE
			SYNTAX SEQUENCE OF Eop0010c01v1Entry
			MAX-ACCESS not-accessible
			STATUS current
			DESCRIPTION
				"Module  EOP0010C01V1 Table"
			::= { eop0010c01v1 1 }

		-- 1.3.6.1.4.1.10106.3.380001.1.1
		eop0010c01v1Entry  OBJECT-TYPE
			SYNTAX Eop0010c01v1Entry
			MAX-ACCESS not-accessible
			STATUS current
			DESCRIPTION
				"Module EOP0010C01V1 Entry"
			INDEX { eop0010c01v1Index }
			::= { eop0010c01v1Table 1 }

			Eop0010c01v1Entry ::=
			SEQUENCE {
				eop0010c01v1Index
				ModuleIndex,
				eop0010c01v1ForceAdjacent
				Bit0No1Yes,
				eop0010c01v1NoSigA
				BitFail,
				eop0010c01v1NoSigATrapEnable
				AlarmEnable,
				eop0010c01v1UnlockA
				BitFail,
				eop0010c01v1UnlockATrapEnable
				AlarmEnable,
				eop0010c01v1LFailA
				BitFail,
				eop0010c01v1LFailATrapEnable
				AlarmEnable,
				eop0010c01v1NoSigB
				BitFail,
				eop0010c01v1NoSigBTrapEnable
				AlarmEnable,
				eop0010c01v1UnlockB
				BitFail,
				eop0010c01v1UnlockBTrapEnable
				AlarmEnable,
				eop0010c01v1LFailB
				BitFail,
				eop0010c01v1LFailBTrapEnable
				AlarmEnable,
				eop0010c01v1SfpId
				SfpType,
				eop0010c01v1SfpSn
				SerialNo,
				eop0010c01v1Temperature
				Temperature0c1,
				eop0010c01v1RxPowerA
				OptPowerX2Uw,
				eop0010c01v1RxPowerB
				OptPowerX2Uw
			 }

		-- 1.3.6.1.4.1.10106.3.101291.1.1.1
		eop0010c01v1Index OBJECT-TYPE
			SYNTAX ModuleIndex
			MAX-ACCESS read-only
			STATUS current
			DESCRIPTION
				"Index of EOP0010C01V1 Table"
		::= { eop0010c01v1Entry 1 }

		-- 1.3.6.1.4.1.10106.3.101291.1.1.3
		eop0010c01v1ForceAdjacent OBJECT-TYPE
			SYNTAX Bit0No1Yes
			MAX-ACCESS read-write
			STATUS current
			DESCRIPTION
				"Inputs from adjacent section"
		::= { eop0010c01v1Entry 3 }

		-- 1.3.6.1.4.1.10106.3.101291.1.1.5
		eop0010c01v1NoSigA OBJECT-TYPE
			SYNTAX BitFail
			MAX-ACCESS read-only
			STATUS current
			DESCRIPTION
				"Input signal status"
		::= { eop0010c01v1Entry 5 }

		-- 1.3.6.1.4.1.10106.3.101291.1.1.6
		eop0010c01v1NoSigATrapEnable OBJECT-TYPE
			SYNTAX AlarmEnable
			MAX-ACCESS read-write
			STATUS current
			DESCRIPTION
				"Input signal status Trap Enable"
		::= { eop0010c01v1Entry 6 }

		-- 1.3.6.1.4.1.10106.3.101291.1.1.7
		eop0010c01v1UnlockA OBJECT-TYPE
			SYNTAX BitFail
			MAX-ACCESS read-only
			STATUS current
			DESCRIPTION
				"Indicates signal unlock fail"
		::= { eop0010c01v1Entry 7 }

		-- 1.3.6.1.4.1.10106.3.101291.1.1.8
		eop0010c01v1UnlockATrapEnable OBJECT-TYPE
			SYNTAX AlarmEnable
			MAX-ACCESS read-write
			STATUS current
			DESCRIPTION
				"Indicates signal unlock fail Trap Enable"
		::= { eop0010c01v1Entry 8 }

		-- 1.3.6.1.4.1.10106.3.101291.1.1.9
		eop0010c01v1LFailA OBJECT-TYPE
			SYNTAX BitFail
			MAX-ACCESS read-only
			STATUS current
			DESCRIPTION
				"Indicates a fail in laser"
		::= { eop0010c01v1Entry 9 }

		-- 1.3.6.1.4.1.10106.3.101291.1.1.10
		eop0010c01v1LFailATrapEnable OBJECT-TYPE
			SYNTAX AlarmEnable
			MAX-ACCESS read-write
			STATUS current
			DESCRIPTION
				"Indicates a fail in laser Trap Enable"
		::= { eop0010c01v1Entry 10 }

		-- 1.3.6.1.4.1.10106.3.101291.1.1.11
		eop0010c01v1NoSigB OBJECT-TYPE
			SYNTAX BitFail
			MAX-ACCESS read-only
			STATUS current
			DESCRIPTION
				"Input signal status"
		::= { eop0010c01v1Entry 11 }

		-- 1.3.6.1.4.1.10106.3.101291.1.1.12
		eop0010c01v1NoSigBTrapEnable OBJECT-TYPE
			SYNTAX AlarmEnable
			MAX-ACCESS read-write
			STATUS current
			DESCRIPTION
				"Input signal status Trap Enable"
		::= { eop0010c01v1Entry 12 }

		-- 1.3.6.1.4.1.10106.3.101291.1.1.13
		eop0010c01v1UnlockB OBJECT-TYPE
			SYNTAX BitFail
			MAX-ACCESS read-only
			STATUS current
			DESCRIPTION
				"Indicates signal unlock fail"
		::= { eop0010c01v1Entry 13 }

		-- 1.3.6.1.4.1.10106.3.101291.1.1.14
		eop0010c01v1UnlockBTrapEnable OBJECT-TYPE
			SYNTAX AlarmEnable
			MAX-ACCESS read-write
			STATUS current
			DESCRIPTION
				"Indicates signal unlock fail Trap Enable"
		::= { eop0010c01v1Entry 14 }

		-- 1.3.6.1.4.1.10106.3.101291.1.1.15
		eop0010c01v1LFailB OBJECT-TYPE
			SYNTAX BitFail
			MAX-ACCESS read-only
			STATUS current
			DESCRIPTION
				"Indicates a fail in laser"
		::= { eop0010c01v1Entry 15 }

		-- 1.3.6.1.4.1.10106.3.101291.1.1.16
		eop0010c01v1LFailBTrapEnable OBJECT-TYPE
			SYNTAX AlarmEnable
			MAX-ACCESS read-write
			STATUS current
			DESCRIPTION
				"Indicates a fail in laser Trap Enable"
		::= { eop0010c01v1Entry 16 }

		-- 1.3.6.1.4.1.10106.3.101291.1.1.17
		eop0010c01v1SfpId OBJECT-TYPE
			SYNTAX SfpType
			MAX-ACCESS read-only
			STATUS current
			DESCRIPTION
				"Indicates the presence of a SFP module"
		::= { eop0010c01v1Entry 17 }

		-- 1.3.6.1.4.1.10106.3.101291.1.1.19
		eop0010c01v1SfpSn OBJECT-TYPE
			SYNTAX SerialNo
			MAX-ACCESS read-only
			STATUS current
			DESCRIPTION
				"SFP Serial number"
		::= { eop0010c01v1Entry 19 }

		-- 1.3.6.1.4.1.10106.3.101291.1.1.21
		eop0010c01v1Temperature OBJECT-TYPE
			SYNTAX Temperature0c1
			MAX-ACCESS read-only
			STATUS current
			DESCRIPTION
				"SFP module temperatura"
		::= { eop0010c01v1Entry 21 }

		-- 1.3.6.1.4.1.10106.3.101291.1.1.23
		eop0010c01v1RxPowerA OBJECT-TYPE
			SYNTAX OptPowerX2Uw
			MAX-ACCESS read-only
			STATUS current
			DESCRIPTION
				"Optical received power"
		::= { eop0010c01v1Entry 23 }

		-- 1.3.6.1.4.1.10106.3.101291.1.1.25
		eop0010c01v1RxPowerB OBJECT-TYPE
			SYNTAX OptPowerX2Uw
			MAX-ACCESS read-only
			STATUS current
			DESCRIPTION
				"Optical received power"
		::= { eop0010c01v1Entry 25 }

		-- 1.3.6.1.4.1.10106.3.382501
		hap3000c01v1 OBJECT IDENTIFIER ::= { albalaProducts 382501 }

		-- 1.3.6.1.4.1.10106.3.382501.1
		hap3000c01v1Table  OBJECT-TYPE
			SYNTAX SEQUENCE OF Hap3000c01v1Entry
			MAX-ACCESS not-accessible
			STATUS current
			DESCRIPTION
				"Module  HAP3000C01V1 Table"
			::= { hap3000c01v1 1 }

		-- 1.3.6.1.4.1.10106.3.382501.1.1
		hap3000c01v1Entry  OBJECT-TYPE
			SYNTAX Hap3000c01v1Entry
			MAX-ACCESS not-accessible
			STATUS current
			DESCRIPTION
				"Module HAP3000C01V1 Entry"
			INDEX { hap3000c01v1Index }
			::= { hap3000c01v1Table 1 }

			Hap3000c01v1Entry ::=
			SEQUENCE {
				hap3000c01v1Index
				ModuleIndex,
				hap3000c01v1ActivePreset
				Preset16Active,
				hap3000c01v1LoadPreset
				Preset16Load,
				hap3000c01v1SavePreset
				Preset16Save,
				hap3000c01v1SynchroMode
				Bit0Fra1Lin,
				hap3000c01v1FailMode
				Bit0Fre1Blk,
				hap3000c01v1DelayMode
				Bit0Syn1De2,
				hap3000c01v1HDelay
				DelayPixel5,
				hap3000c01v1FrameDelay
				DelayFram4,
				hap3000c01v1VDelay
				DelayLines2,
				hap3000c01v1Grp12Mult
				BitMultichnl,
				hap3000c01v1Grp34Mult
				BitMultichnl,
				hap3000c01v1Grp1P0Mode
				Bit0Ste1Mon,
				hap3000c01v1Grp1P1Mode
				Bit0Ste1Mon,
				hap3000c01v1Grp2P0Mode
				Bit0Ste1Mon,
				hap3000c01v1Grp2P1Mode
				Bit0Ste1Mon,
				hap3000c01v1Grp3P0Mode
				Bit0Ste1Mon,
				hap3000c01v1Grp3P1Mode
				Bit0Ste1Mon,
				hap3000c01v1Grp4P0Mode
				Bit0Ste1Mon,
				hap3000c01v1Grp4P1Mode
				Bit0Ste1Mon,
				hap3000c01v1ProcessingG1p0
				Bit0Dis1Ena,
				hap3000c01v1ProcessingG1p1
				Bit0Dis1Ena,
				hap3000c01v1ProcessingG2p0
				Bit0Dis1Ena,
				hap3000c01v1ProcessingG2p1
				Bit0Dis1Ena,
				hap3000c01v1ProcessingG3p0
				Bit0Dis1Ena,
				hap3000c01v1ProcessingG3p1
				Bit0Dis1Ena,
				hap3000c01v1ProcessingG4p0
				Bit0Dis1Ena,
				hap3000c01v1ProcessingG4p1
				Bit0Dis1Ena,
				hap3000c01v1LimiterG1p0
				BitMask,
				hap3000c01v1LimiterG1p1
				BitMask,
				hap3000c01v1LimiterG2p0
				BitMask,
				hap3000c01v1LimiterG2p1
				BitMask,
				hap3000c01v1LimiterG3p0
				BitMask,
				hap3000c01v1LimiterG3p1
				BitMask,
				hap3000c01v1LimiterG4p0
				BitMask,
				hap3000c01v1LimiterG4p1
				BitMask,
				hap3000c01v1TransientG1p0
				BitMask,
				hap3000c01v1TransientG1p1
				BitMask,
				hap3000c01v1TransientG2p0
				BitMask,
				hap3000c01v1TransientG2p1
				BitMask,
				hap3000c01v1TransientG3p0
				BitMask,
				hap3000c01v1TransientG3p1
				BitMask,
				hap3000c01v1TransientG4p0
				BitMask,
				hap3000c01v1TransientG4p1
				BitMask,
				hap3000c01v1LoudnessG1p0
				BitMask,
				hap3000c01v1LoudnessG1p1
				BitMask,
				hap3000c01v1LoudnessG2p0
				BitMask,
				hap3000c01v1LoudnessG2p1
				BitMask,
				hap3000c01v1LoudnessG3p0
				BitMask,
				hap3000c01v1LoudnessG3p1
				BitMask,
				hap3000c01v1LoudnessG4p0
				BitMask,
				hap3000c01v1LoudnessG4p1
				BitMask,
				hap3000c01v1LoudTarg
				LevelLkfs2,
				hap3000c01v1TruePeakMax
				LevelDbfs8,
				hap3000c01v1Grp1P0A
				AudioMxInput5,
				hap3000c01v1Grp1P1A
				AudioMxInput5,
				hap3000c01v1Grp2P0A
				AudioMxInput5,
				hap3000c01v1Grp2P1A
				AudioMxInput5,
				hap3000c01v1Grp3P0A
				AudioMxInput5,
				hap3000c01v1Grp3P1A
				AudioMxInput5,
				hap3000c01v1Grp4P0A
				AudioMxInput5,
				hap3000c01v1Grp4P1A
				AudioMxInput5,
				hap3000c01v1MeasPlace
				Bit0In1Out,
				hap3000c01v1SelLoudMeas
				LoudnessType,
				hap3000c01v1StatMeas
				Bit0LdBit1Pk,
				hap3000c01v1OsdEnable
				Bit0Dis1Ena,
				hap3000c01v1DispPeak
				Bit0Dis1Ena,
				hap3000c01v1DispLoudness
				Bit0Dis1Ena,
				hap3000c01v1Meter1
				BitMask,
				hap3000c01v1Meter2
				BitMask,
				hap3000c01v1Meter3
				BitMask,
				hap3000c01v1Meter4
				BitMask,
				hap3000c01v1Meter5
				BitMask,
				hap3000c01v1Meter6
				BitMask,
				hap3000c01v1Meter7
				BitMask,
				hap3000c01v1Meter8
				BitMask,
				hap3000c01v1DispMode
				PpmDistrib,
				hap3000c01v1StatFlash
				BitFailN,
				hap3000c01v1NoSig
				BitFail,
				hap3000c01v1NoSigTrapEnable
				AlarmEnable,
				hap3000c01v1Unlock
				BitFail,
				hap3000c01v1UnlockTrapEnable
				AlarmEnable,
				hap3000c01v1EdhCrc
				BitFail,
				hap3000c01v1EdhCrcTrapEnable
				AlarmEnable,
				hap3000c01v1NoRef
				BitFail,
				hap3000c01v1NoRefTrapEnable
				AlarmEnable,
				hap3000c01v1RefUnlck
				BitFail,
				hap3000c01v1RefUnlckTrapEnable
				AlarmEnable,
				hap3000c01v1AudioFail
				BitFail,
				hap3000c01v1AudioFailTrapEnable
				AlarmEnable,
				hap3000c01v1FormatIn
				SdiHd3gFmt3,
				hap3000c01v1FormatRef
				SdiHd3gFmt3,
				hap3000c01v1SigDelay
				DelayX20Us,
				hap3000c01v1SerialNo
				SerialNo
			 }

		-- 1.3.6.1.4.1.10106.3.101291.1.1.1
		hap3000c01v1Index OBJECT-TYPE
			SYNTAX ModuleIndex
			MAX-ACCESS read-only
			STATUS current
			DESCRIPTION
				"Index of HAP3000C01V1 Table"
		::= { hap3000c01v1Entry 1 }

		-- 1.3.6.1.4.1.10106.3.101291.1.1.3
		hap3000c01v1ActivePreset OBJECT-TYPE
			SYNTAX Preset16Active
			MAX-ACCESS read-only
			STATUS current
			DESCRIPTION
				"Shows the active preset"
		::= { hap3000c01v1Entry 3 }

		-- 1.3.6.1.4.1.10106.3.101291.1.1.5
		hap3000c01v1LoadPreset OBJECT-TYPE
			SYNTAX Preset16Load
			MAX-ACCESS read-write
			STATUS current
			DESCRIPTION
				"Allows loading a preset"
		::= { hap3000c01v1Entry 5 }

		-- 1.3.6.1.4.1.10106.3.101291.1.1.7
		hap3000c01v1SavePreset OBJECT-TYPE
			SYNTAX Preset16Save
			MAX-ACCESS read-write
			STATUS current
			DESCRIPTION
				"Allows saving a preset"
		::= { hap3000c01v1Entry 7 }

		-- 1.3.6.1.4.1.10106.3.101291.1.1.9
		hap3000c01v1SynchroMode OBJECT-TYPE
			SYNTAX Bit0Fra1Lin
			MAX-ACCESS read-write
			STATUS current
			DESCRIPTION
				"Allows selecting the synchronizing mode"
		::= { hap3000c01v1Entry 9 }

		-- 1.3.6.1.4.1.10106.3.101291.1.1.11
		hap3000c01v1FailMode OBJECT-TYPE
			SYNTAX Bit0Fre1Blk
			MAX-ACCESS read-write
			STATUS current
			DESCRIPTION
				"Allows selecting the output video signal if the input fails"
		::= { hap3000c01v1Entry 11 }

		-- 1.3.6.1.4.1.10106.3.101291.1.1.13
		hap3000c01v1DelayMode OBJECT-TYPE
			SYNTAX Bit0Syn1De2
			MAX-ACCESS read-write
			STATUS current
			DESCRIPTION
				"Allows selecting the operating mode"
		::= { hap3000c01v1Entry 13 }

		-- 1.3.6.1.4.1.10106.3.101291.1.1.15
		hap3000c01v1HDelay OBJECT-TYPE
			SYNTAX DelayPixel5
			MAX-ACCESS read-write
			STATUS current
			DESCRIPTION
				"Allows adjusting the video horizontal delay"
		::= { hap3000c01v1Entry 15 }

		-- 1.3.6.1.4.1.10106.3.101291.1.1.17
		hap3000c01v1FrameDelay OBJECT-TYPE
			SYNTAX DelayFram4
			MAX-ACCESS read-write
			STATUS current
			DESCRIPTION
				"Allows adjusting the frame delay"
		::= { hap3000c01v1Entry 17 }

		-- 1.3.6.1.4.1.10106.3.101291.1.1.19
		hap3000c01v1VDelay OBJECT-TYPE
			SYNTAX DelayLines2
			MAX-ACCESS read-write
			STATUS current
			DESCRIPTION
				"Allows adjusting the video vertical delay"
		::= { hap3000c01v1Entry 19 }

		-- 1.3.6.1.4.1.10106.3.101291.1.1.21
		hap3000c01v1Grp12Mult OBJECT-TYPE
			SYNTAX BitMultichnl
			MAX-ACCESS read-write
			STATUS current
			DESCRIPTION
				"Allows selecting multichannel audio in groups 1 and 2"
		::= { hap3000c01v1Entry 21 }

		-- 1.3.6.1.4.1.10106.3.101291.1.1.23
		hap3000c01v1Grp34Mult OBJECT-TYPE
			SYNTAX BitMultichnl
			MAX-ACCESS read-write
			STATUS current
			DESCRIPTION
				"Allows selecting multichannel audio in groups 3 and 4"
		::= { hap3000c01v1Entry 23 }

		-- 1.3.6.1.4.1.10106.3.101291.1.1.25
		hap3000c01v1Grp1P0Mode OBJECT-TYPE
			SYNTAX Bit0Ste1Mon
			MAX-ACCESS read-write
			STATUS current
			DESCRIPTION
				"Allows selecting audio type in group 1 pair 0"
		::= { hap3000c01v1Entry 25 }

		-- 1.3.6.1.4.1.10106.3.101291.1.1.27
		hap3000c01v1Grp1P1Mode OBJECT-TYPE
			SYNTAX Bit0Ste1Mon
			MAX-ACCESS read-write
			STATUS current
			DESCRIPTION
				"Allows selecting audio type in group 1 pair 1"
		::= { hap3000c01v1Entry 27 }

		-- 1.3.6.1.4.1.10106.3.101291.1.1.29
		hap3000c01v1Grp2P0Mode OBJECT-TYPE
			SYNTAX Bit0Ste1Mon
			MAX-ACCESS read-write
			STATUS current
			DESCRIPTION
				"Allows selecting audio type in group 2 pair 0"
		::= { hap3000c01v1Entry 29 }

		-- 1.3.6.1.4.1.10106.3.101291.1.1.31
		hap3000c01v1Grp2P1Mode OBJECT-TYPE
			SYNTAX Bit0Ste1Mon
			MAX-ACCESS read-write
			STATUS current
			DESCRIPTION
				"Allows selecting audio type in group 2 pair 1"
		::= { hap3000c01v1Entry 31 }

		-- 1.3.6.1.4.1.10106.3.101291.1.1.33
		hap3000c01v1Grp3P0Mode OBJECT-TYPE
			SYNTAX Bit0Ste1Mon
			MAX-ACCESS read-write
			STATUS current
			DESCRIPTION
				"Allows selecting audio type in group 3 pair 0"
		::= { hap3000c01v1Entry 33 }

		-- 1.3.6.1.4.1.10106.3.101291.1.1.35
		hap3000c01v1Grp3P1Mode OBJECT-TYPE
			SYNTAX Bit0Ste1Mon
			MAX-ACCESS read-write
			STATUS current
			DESCRIPTION
				"Allows selecting audio type in group 3 pair 1"
		::= { hap3000c01v1Entry 35 }

		-- 1.3.6.1.4.1.10106.3.101291.1.1.37
		hap3000c01v1Grp4P0Mode OBJECT-TYPE
			SYNTAX Bit0Ste1Mon
			MAX-ACCESS read-write
			STATUS current
			DESCRIPTION
				"Allows selecting audio type in group 4 pair 0"
		::= { hap3000c01v1Entry 37 }

		-- 1.3.6.1.4.1.10106.3.101291.1.1.39
		hap3000c01v1Grp4P1Mode OBJECT-TYPE
			SYNTAX Bit0Ste1Mon
			MAX-ACCESS read-write
			STATUS current
			DESCRIPTION
				"Allows selecting audio type in group 4 pair 1"
		::= { hap3000c01v1Entry 39 }

		-- 1.3.6.1.4.1.10106.3.101291.1.1.41
		hap3000c01v1ProcessingG1p0 OBJECT-TYPE
			SYNTAX Bit0Dis1Ena
			MAX-ACCESS read-write
			STATUS current
			DESCRIPTION
				"Allows processing the audio in group 1 pair 0"
		::= { hap3000c01v1Entry 41 }

		-- 1.3.6.1.4.1.10106.3.101291.1.1.43
		hap3000c01v1ProcessingG1p1 OBJECT-TYPE
			SYNTAX Bit0Dis1Ena
			MAX-ACCESS read-write
			STATUS current
			DESCRIPTION
				"Allows processing the audio in group 1 pair 1"
		::= { hap3000c01v1Entry 43 }

		-- 1.3.6.1.4.1.10106.3.101291.1.1.45
		hap3000c01v1ProcessingG2p0 OBJECT-TYPE
			SYNTAX Bit0Dis1Ena
			MAX-ACCESS read-write
			STATUS current
			DESCRIPTION
				"Allows processing the audio in group 2 pair 0"
		::= { hap3000c01v1Entry 45 }

		-- 1.3.6.1.4.1.10106.3.101291.1.1.47
		hap3000c01v1ProcessingG2p1 OBJECT-TYPE
			SYNTAX Bit0Dis1Ena
			MAX-ACCESS read-write
			STATUS current
			DESCRIPTION
				"Allows processing the audio in group 2 pair 1"
		::= { hap3000c01v1Entry 47 }

		-- 1.3.6.1.4.1.10106.3.101291.1.1.49
		hap3000c01v1ProcessingG3p0 OBJECT-TYPE
			SYNTAX Bit0Dis1Ena
			MAX-ACCESS read-write
			STATUS current
			DESCRIPTION
				"Allows processing the audio in group 3 pair 0"
		::= { hap3000c01v1Entry 49 }

		-- 1.3.6.1.4.1.10106.3.101291.1.1.51
		hap3000c01v1ProcessingG3p1 OBJECT-TYPE
			SYNTAX Bit0Dis1Ena
			MAX-ACCESS read-write
			STATUS current
			DESCRIPTION
				"Allows processing the audio in group 3 pair 1"
		::= { hap3000c01v1Entry 51 }

		-- 1.3.6.1.4.1.10106.3.101291.1.1.53
		hap3000c01v1ProcessingG4p0 OBJECT-TYPE
			SYNTAX Bit0Dis1Ena
			MAX-ACCESS read-write
			STATUS current
			DESCRIPTION
				"Allows processing the audio in group 4 pair 0"
		::= { hap3000c01v1Entry 53 }

		-- 1.3.6.1.4.1.10106.3.101291.1.1.55
		hap3000c01v1ProcessingG4p1 OBJECT-TYPE
			SYNTAX Bit0Dis1Ena
			MAX-ACCESS read-write
			STATUS current
			DESCRIPTION
				"Allows processing the audio in group 4 pair 1"
		::= { hap3000c01v1Entry 55 }

		-- 1.3.6.1.4.1.10106.3.101291.1.1.57
		hap3000c01v1LimiterG1p0 OBJECT-TYPE
			SYNTAX BitMask
			MAX-ACCESS read-write
			STATUS current
			DESCRIPTION
				"Enables the peak limiter for group 1 pair 0"
		::= { hap3000c01v1Entry 57 }

		-- 1.3.6.1.4.1.10106.3.101291.1.1.59
		hap3000c01v1LimiterG1p1 OBJECT-TYPE
			SYNTAX BitMask
			MAX-ACCESS read-write
			STATUS current
			DESCRIPTION
				"Enables the peak limiter for group 1 pair 1"
		::= { hap3000c01v1Entry 59 }

		-- 1.3.6.1.4.1.10106.3.101291.1.1.61
		hap3000c01v1LimiterG2p0 OBJECT-TYPE
			SYNTAX BitMask
			MAX-ACCESS read-write
			STATUS current
			DESCRIPTION
				"Enables the peak limiter for group 2 pair 0"
		::= { hap3000c01v1Entry 61 }

		-- 1.3.6.1.4.1.10106.3.101291.1.1.63
		hap3000c01v1LimiterG2p1 OBJECT-TYPE
			SYNTAX BitMask
			MAX-ACCESS read-write
			STATUS current
			DESCRIPTION
				"Enables the peak limiter for group 2 pair 1"
		::= { hap3000c01v1Entry 63 }

		-- 1.3.6.1.4.1.10106.3.101291.1.1.65
		hap3000c01v1LimiterG3p0 OBJECT-TYPE
			SYNTAX BitMask
			MAX-ACCESS read-write
			STATUS current
			DESCRIPTION
				"Enables the peak limiter for group 3 pair 0"
		::= { hap3000c01v1Entry 65 }

		-- 1.3.6.1.4.1.10106.3.101291.1.1.67
		hap3000c01v1LimiterG3p1 OBJECT-TYPE
			SYNTAX BitMask
			MAX-ACCESS read-write
			STATUS current
			DESCRIPTION
				"Enables the peak limiter for group 3 pair 1"
		::= { hap3000c01v1Entry 67 }

		-- 1.3.6.1.4.1.10106.3.101291.1.1.69
		hap3000c01v1LimiterG4p0 OBJECT-TYPE
			SYNTAX BitMask
			MAX-ACCESS read-write
			STATUS current
			DESCRIPTION
				"Enables the peak limiter for group 4 pair 0"
		::= { hap3000c01v1Entry 69 }

		-- 1.3.6.1.4.1.10106.3.101291.1.1.71
		hap3000c01v1LimiterG4p1 OBJECT-TYPE
			SYNTAX BitMask
			MAX-ACCESS read-write
			STATUS current
			DESCRIPTION
				"Enables the peak limiter for group 4 pair 1"
		::= { hap3000c01v1Entry 71 }

		-- 1.3.6.1.4.1.10106.3.101291.1.1.73
		hap3000c01v1TransientG1p0 OBJECT-TYPE
			SYNTAX BitMask
			MAX-ACCESS read-write
			STATUS current
			DESCRIPTION
				"Enables the transient processing for group 1 pair 0"
		::= { hap3000c01v1Entry 73 }

		-- 1.3.6.1.4.1.10106.3.101291.1.1.75
		hap3000c01v1TransientG1p1 OBJECT-TYPE
			SYNTAX BitMask
			MAX-ACCESS read-write
			STATUS current
			DESCRIPTION
				"Enables the transient processing for group 1 pair 1"
		::= { hap3000c01v1Entry 75 }

		-- 1.3.6.1.4.1.10106.3.101291.1.1.77
		hap3000c01v1TransientG2p0 OBJECT-TYPE
			SYNTAX BitMask
			MAX-ACCESS read-write
			STATUS current
			DESCRIPTION
				"Enables the transient processing for group 2 pair 0"
		::= { hap3000c01v1Entry 77 }

		-- 1.3.6.1.4.1.10106.3.101291.1.1.79
		hap3000c01v1TransientG2p1 OBJECT-TYPE
			SYNTAX BitMask
			MAX-ACCESS read-write
			STATUS current
			DESCRIPTION
				"Enables the transient processing for group 2 pair 1"
		::= { hap3000c01v1Entry 79 }

		-- 1.3.6.1.4.1.10106.3.101291.1.1.81
		hap3000c01v1TransientG3p0 OBJECT-TYPE
			SYNTAX BitMask
			MAX-ACCESS read-write
			STATUS current
			DESCRIPTION
				"Enables the transient processing for group 3 pair 0"
		::= { hap3000c01v1Entry 81 }

		-- 1.3.6.1.4.1.10106.3.101291.1.1.83
		hap3000c01v1TransientG3p1 OBJECT-TYPE
			SYNTAX BitMask
			MAX-ACCESS read-write
			STATUS current
			DESCRIPTION
				"Enables the transient processing for group 3 pair 1"
		::= { hap3000c01v1Entry 83 }

		-- 1.3.6.1.4.1.10106.3.101291.1.1.85
		hap3000c01v1TransientG4p0 OBJECT-TYPE
			SYNTAX BitMask
			MAX-ACCESS read-write
			STATUS current
			DESCRIPTION
				"Enables the transient processing for group 4 pair 0"
		::= { hap3000c01v1Entry 85 }

		-- 1.3.6.1.4.1.10106.3.101291.1.1.87
		hap3000c01v1TransientG4p1 OBJECT-TYPE
			SYNTAX BitMask
			MAX-ACCESS read-write
			STATUS current
			DESCRIPTION
				"Enables the transient processing for group 4 pair 1"
		::= { hap3000c01v1Entry 87 }

		-- 1.3.6.1.4.1.10106.3.101291.1.1.89
		hap3000c01v1LoudnessG1p0 OBJECT-TYPE
			SYNTAX BitMask
			MAX-ACCESS read-write
			STATUS current
			DESCRIPTION
				"Enables the loudness normalizer for group 1 pair 0"
		::= { hap3000c01v1Entry 89 }

		-- 1.3.6.1.4.1.10106.3.101291.1.1.91
		hap3000c01v1LoudnessG1p1 OBJECT-TYPE
			SYNTAX BitMask
			MAX-ACCESS read-write
			STATUS current
			DESCRIPTION
				"Enables the loudness normalizer for group 1 pair 1"
		::= { hap3000c01v1Entry 91 }

		-- 1.3.6.1.4.1.10106.3.101291.1.1.93
		hap3000c01v1LoudnessG2p0 OBJECT-TYPE
			SYNTAX BitMask
			MAX-ACCESS read-write
			STATUS current
			DESCRIPTION
				"Enables the loudness normalizer for group 2 pair 0"
		::= { hap3000c01v1Entry 93 }

		-- 1.3.6.1.4.1.10106.3.101291.1.1.95
		hap3000c01v1LoudnessG2p1 OBJECT-TYPE
			SYNTAX BitMask
			MAX-ACCESS read-write
			STATUS current
			DESCRIPTION
				"Enables the loudness normalizer for group 2 pair 1"
		::= { hap3000c01v1Entry 95 }

		-- 1.3.6.1.4.1.10106.3.101291.1.1.97
		hap3000c01v1LoudnessG3p0 OBJECT-TYPE
			SYNTAX BitMask
			MAX-ACCESS read-write
			STATUS current
			DESCRIPTION
				"Enables the loudness normalizer for group 3 pair 0"
		::= { hap3000c01v1Entry 97 }

		-- 1.3.6.1.4.1.10106.3.101291.1.1.99
		hap3000c01v1LoudnessG3p1 OBJECT-TYPE
			SYNTAX BitMask
			MAX-ACCESS read-write
			STATUS current
			DESCRIPTION
				"Enables the loudness normalizer for group 3 pair 1"
		::= { hap3000c01v1Entry 99 }

		-- 1.3.6.1.4.1.10106.3.101291.1.1.101
		hap3000c01v1LoudnessG4p0 OBJECT-TYPE
			SYNTAX BitMask
			MAX-ACCESS read-write
			STATUS current
			DESCRIPTION
				"Enables the loudness normalizer for group 4 pair 0"
		::= { hap3000c01v1Entry 101 }

		-- 1.3.6.1.4.1.10106.3.101291.1.1.103
		hap3000c01v1LoudnessG4p1 OBJECT-TYPE
			SYNTAX BitMask
			MAX-ACCESS read-write
			STATUS current
			DESCRIPTION
				"Enables the loudness normalizer for group 4 pair 1"
		::= { hap3000c01v1Entry 103 }

		-- 1.3.6.1.4.1.10106.3.101291.1.1.105
		hap3000c01v1LoudTarg OBJECT-TYPE
			SYNTAX LevelLkfs2
			MAX-ACCESS read-write
			STATUS current
			DESCRIPTION
				"Integral loudness target"
		::= { hap3000c01v1Entry 105 }

		-- 1.3.6.1.4.1.10106.3.101291.1.1.107
		hap3000c01v1TruePeakMax OBJECT-TYPE
			SYNTAX LevelDbfs8
			MAX-ACCESS read-write
			STATUS current
			DESCRIPTION
				"Maximum level for the audio signal true peak"
		::= { hap3000c01v1Entry 107 }

		-- 1.3.6.1.4.1.10106.3.101291.1.1.109
		hap3000c01v1Grp1P0A OBJECT-TYPE
			SYNTAX AudioMxInput5
			MAX-ACCESS read-write
			STATUS current
			DESCRIPTION
				"Allows selecting the audio embedded in group 1 pair 0"
		::= { hap3000c01v1Entry 109 }

		-- 1.3.6.1.4.1.10106.3.101291.1.1.111
		hap3000c01v1Grp1P1A OBJECT-TYPE
			SYNTAX AudioMxInput5
			MAX-ACCESS read-write
			STATUS current
			DESCRIPTION
				"Allows selecting the audio embedded in group 1 pair 1"
		::= { hap3000c01v1Entry 111 }

		-- 1.3.6.1.4.1.10106.3.101291.1.1.113
		hap3000c01v1Grp2P0A OBJECT-TYPE
			SYNTAX AudioMxInput5
			MAX-ACCESS read-write
			STATUS current
			DESCRIPTION
				"Allows selecting the audio embedded in group 2 pair 0"
		::= { hap3000c01v1Entry 113 }

		-- 1.3.6.1.4.1.10106.3.101291.1.1.115
		hap3000c01v1Grp2P1A OBJECT-TYPE
			SYNTAX AudioMxInput5
			MAX-ACCESS read-write
			STATUS current
			DESCRIPTION
				"Allows selecting the audio embedded in group 2 pair 1"
		::= { hap3000c01v1Entry 115 }

		-- 1.3.6.1.4.1.10106.3.101291.1.1.117
		hap3000c01v1Grp3P0A OBJECT-TYPE
			SYNTAX AudioMxInput5
			MAX-ACCESS read-write
			STATUS current
			DESCRIPTION
				"Allows selecting the audio embedded in group 3 pair 0"
		::= { hap3000c01v1Entry 117 }

		-- 1.3.6.1.4.1.10106.3.101291.1.1.119
		hap3000c01v1Grp3P1A OBJECT-TYPE
			SYNTAX AudioMxInput5
			MAX-ACCESS read-write
			STATUS current
			DESCRIPTION
				"Allows selecting the audio embedded in group 3 pair 1"
		::= { hap3000c01v1Entry 119 }

		-- 1.3.6.1.4.1.10106.3.101291.1.1.121
		hap3000c01v1Grp4P0A OBJECT-TYPE
			SYNTAX AudioMxInput5
			MAX-ACCESS read-write
			STATUS current
			DESCRIPTION
				"Allows selecting the audio embedded in group 4 pair 0"
		::= { hap3000c01v1Entry 121 }

		-- 1.3.6.1.4.1.10106.3.101291.1.1.123
		hap3000c01v1Grp4P1A OBJECT-TYPE
			SYNTAX AudioMxInput5
			MAX-ACCESS read-write
			STATUS current
			DESCRIPTION
				"Allows selecting the audio embedded in group 4 pair 1"
		::= { hap3000c01v1Entry 123 }

		-- 1.3.6.1.4.1.10106.3.101291.1.1.125
		hap3000c01v1MeasPlace OBJECT-TYPE
			SYNTAX Bit0In1Out
			MAX-ACCESS read-write
			STATUS current
			DESCRIPTION
				"Allows selecting the point in which the measure is performed"
		::= { hap3000c01v1Entry 125 }

		-- 1.3.6.1.4.1.10106.3.101291.1.1.127
		hap3000c01v1SelLoudMeas OBJECT-TYPE
			SYNTAX LoudnessType
			MAX-ACCESS read-write
			STATUS current
			DESCRIPTION
				"Allows selecting the kind of loudness measure to be displayed"
		::= { hap3000c01v1Entry 127 }

		-- 1.3.6.1.4.1.10106.3.101291.1.1.129
		hap3000c01v1StatMeas OBJECT-TYPE
			SYNTAX Bit0LdBit1Pk
			MAX-ACCESS read-write
			STATUS current
			DESCRIPTION
				"Allows selecting the kind of measure to be displayed in the state registers"
		::= { hap3000c01v1Entry 129 }

		-- 1.3.6.1.4.1.10106.3.101291.1.1.131
		hap3000c01v1OsdEnable OBJECT-TYPE
			SYNTAX Bit0Dis1Ena
			MAX-ACCESS read-write
			STATUS current
			DESCRIPTION
				"Enables the On Screen Display"
		::= { hap3000c01v1Entry 131 }

		-- 1.3.6.1.4.1.10106.3.101291.1.1.133
		hap3000c01v1DispPeak OBJECT-TYPE
			SYNTAX Bit0Dis1Ena
			MAX-ACCESS read-write
			STATUS current
			DESCRIPTION
				"Enables the peak represesntation on the OSD"
		::= { hap3000c01v1Entry 133 }

		-- 1.3.6.1.4.1.10106.3.101291.1.1.135
		hap3000c01v1DispLoudness OBJECT-TYPE
			SYNTAX Bit0Dis1Ena
			MAX-ACCESS read-write
			STATUS current
			DESCRIPTION
				"Enables the loudness representation on the OSD"
		::= { hap3000c01v1Entry 135 }

		-- 1.3.6.1.4.1.10106.3.101291.1.1.137
		hap3000c01v1Meter1 OBJECT-TYPE
			SYNTAX BitMask
			MAX-ACCESS read-write
			STATUS current
			DESCRIPTION
				"Displays the meter G1P0 on the OSD"
		::= { hap3000c01v1Entry 137 }

		-- 1.3.6.1.4.1.10106.3.101291.1.1.139
		hap3000c01v1Meter2 OBJECT-TYPE
			SYNTAX BitMask
			MAX-ACCESS read-write
			STATUS current
			DESCRIPTION
				"Displays the meter G1P1 on the OSD"
		::= { hap3000c01v1Entry 139 }

		-- 1.3.6.1.4.1.10106.3.101291.1.1.141
		hap3000c01v1Meter3 OBJECT-TYPE
			SYNTAX BitMask
			MAX-ACCESS read-write
			STATUS current
			DESCRIPTION
				"Displays the meter G2P0 on the OSD"
		::= { hap3000c01v1Entry 141 }

		-- 1.3.6.1.4.1.10106.3.101291.1.1.143
		hap3000c01v1Meter4 OBJECT-TYPE
			SYNTAX BitMask
			MAX-ACCESS read-write
			STATUS current
			DESCRIPTION
				"Displays the meter G2P1 on the OSD"
		::= { hap3000c01v1Entry 143 }

		-- 1.3.6.1.4.1.10106.3.101291.1.1.145
		hap3000c01v1Meter5 OBJECT-TYPE
			SYNTAX BitMask
			MAX-ACCESS read-write
			STATUS current
			DESCRIPTION
				"Displays the meter G3P0 on the OSD"
		::= { hap3000c01v1Entry 145 }

		-- 1.3.6.1.4.1.10106.3.101291.1.1.147
		hap3000c01v1Meter6 OBJECT-TYPE
			SYNTAX BitMask
			MAX-ACCESS read-write
			STATUS current
			DESCRIPTION
				"Displays the meter G3P1 on the OSD"
		::= { hap3000c01v1Entry 147 }

		-- 1.3.6.1.4.1.10106.3.101291.1.1.149
		hap3000c01v1Meter7 OBJECT-TYPE
			SYNTAX BitMask
			MAX-ACCESS read-write
			STATUS current
			DESCRIPTION
				"Displays the meter G4P0 on the OSD"
		::= { hap3000c01v1Entry 149 }

		-- 1.3.6.1.4.1.10106.3.101291.1.1.151
		hap3000c01v1Meter8 OBJECT-TYPE
			SYNTAX BitMask
			MAX-ACCESS read-write
			STATUS current
			DESCRIPTION
				"Displays the meter G4P1 on the OSD"
		::= { hap3000c01v1Entry 151 }

		-- 1.3.6.1.4.1.10106.3.101291.1.1.153
		hap3000c01v1DispMode OBJECT-TYPE
			SYNTAX PpmDistrib
			MAX-ACCESS read-write
			STATUS current
			DESCRIPTION
				"Allows selecting the PPMs distribution: 1 rpw or 2 rows"
		::= { hap3000c01v1Entry 153 }

		-- 1.3.6.1.4.1.10106.3.101291.1.1.155
		hap3000c01v1StatFlash OBJECT-TYPE
			SYNTAX BitFailN
			MAX-ACCESS read-only
			STATUS current
			DESCRIPTION
				"Displays the Flash state"
		::= { hap3000c01v1Entry 155 }

		-- 1.3.6.1.4.1.10106.3.101291.1.1.157
		hap3000c01v1NoSig OBJECT-TYPE
			SYNTAX BitFail
			MAX-ACCESS read-only
			STATUS current
			DESCRIPTION
				"No SDI signal fail"
		::= { hap3000c01v1Entry 157 }

		-- 1.3.6.1.4.1.10106.3.101291.1.1.158
		hap3000c01v1NoSigTrapEnable OBJECT-TYPE
			SYNTAX AlarmEnable
			MAX-ACCESS read-write
			STATUS current
			DESCRIPTION
				"No SDI signal fail Trap Enable"
		::= { hap3000c01v1Entry 158 }

		-- 1.3.6.1.4.1.10106.3.101291.1.1.159
		hap3000c01v1Unlock OBJECT-TYPE
			SYNTAX BitFail
			MAX-ACCESS read-only
			STATUS current
			DESCRIPTION
				"Unlock fail"
		::= { hap3000c01v1Entry 159 }

		-- 1.3.6.1.4.1.10106.3.101291.1.1.160
		hap3000c01v1UnlockTrapEnable OBJECT-TYPE
			SYNTAX AlarmEnable
			MAX-ACCESS read-write
			STATUS current
			DESCRIPTION
				"Unlock fail Trap Enable"
		::= { hap3000c01v1Entry 160 }

		-- 1.3.6.1.4.1.10106.3.101291.1.1.161
		hap3000c01v1EdhCrc OBJECT-TYPE
			SYNTAX BitFail
			MAX-ACCESS read-only
			STATUS current
			DESCRIPTION
				"EDH/CRC errors"
		::= { hap3000c01v1Entry 161 }

		-- 1.3.6.1.4.1.10106.3.101291.1.1.162
		hap3000c01v1EdhCrcTrapEnable OBJECT-TYPE
			SYNTAX AlarmEnable
			MAX-ACCESS read-write
			STATUS current
			DESCRIPTION
				"EDH/CRC errors Trap Enable"
		::= { hap3000c01v1Entry 162 }

		-- 1.3.6.1.4.1.10106.3.101291.1.1.163
		hap3000c01v1NoRef OBJECT-TYPE
			SYNTAX BitFail
			MAX-ACCESS read-only
			STATUS current
			DESCRIPTION
				"No reference signal fail"
		::= { hap3000c01v1Entry 163 }

		-- 1.3.6.1.4.1.10106.3.101291.1.1.164
		hap3000c01v1NoRefTrapEnable OBJECT-TYPE
			SYNTAX AlarmEnable
			MAX-ACCESS read-write
			STATUS current
			DESCRIPTION
				"No reference signal fail Trap Enable"
		::= { hap3000c01v1Entry 164 }

		-- 1.3.6.1.4.1.10106.3.101291.1.1.165
		hap3000c01v1RefUnlck OBJECT-TYPE
			SYNTAX BitFail
			MAX-ACCESS read-only
			STATUS current
			DESCRIPTION
				"Reference input unlock fail"
		::= { hap3000c01v1Entry 165 }

		-- 1.3.6.1.4.1.10106.3.101291.1.1.166
		hap3000c01v1RefUnlckTrapEnable OBJECT-TYPE
			SYNTAX AlarmEnable
			MAX-ACCESS read-write
			STATUS current
			DESCRIPTION
				"Reference input unlock fail Trap Enable"
		::= { hap3000c01v1Entry 166 }

		-- 1.3.6.1.4.1.10106.3.101291.1.1.167
		hap3000c01v1AudioFail OBJECT-TYPE
			SYNTAX BitFail
			MAX-ACCESS read-only
			STATUS current
			DESCRIPTION
				"Audio fail"
		::= { hap3000c01v1Entry 167 }

		-- 1.3.6.1.4.1.10106.3.101291.1.1.168
		hap3000c01v1AudioFailTrapEnable OBJECT-TYPE
			SYNTAX AlarmEnable
			MAX-ACCESS read-write
			STATUS current
			DESCRIPTION
				"Audio fail Trap Enable"
		::= { hap3000c01v1Entry 168 }

		-- 1.3.6.1.4.1.10106.3.101291.1.1.169
		hap3000c01v1FormatIn OBJECT-TYPE
			SYNTAX SdiHd3gFmt3
			MAX-ACCESS read-only
			STATUS current
			DESCRIPTION
				"Indicates the SDI transmited signal format"
		::= { hap3000c01v1Entry 169 }

		-- 1.3.6.1.4.1.10106.3.101291.1.1.171
		hap3000c01v1FormatRef OBJECT-TYPE
			SYNTAX SdiHd3gFmt3
			MAX-ACCESS read-only
			STATUS current
			DESCRIPTION
				"Indicates the reference SDI signal format"
		::= { hap3000c01v1Entry 171 }

		-- 1.3.6.1.4.1.10106.3.101291.1.1.173
		hap3000c01v1SigDelay OBJECT-TYPE
			SYNTAX DelayX20Us
			MAX-ACCESS read-only
			STATUS current
			DESCRIPTION
				"Indicates the input to output delay"
		::= { hap3000c01v1Entry 173 }

		-- 1.3.6.1.4.1.10106.3.101291.1.1.175
		hap3000c01v1SerialNo OBJECT-TYPE
			SYNTAX SerialNo
			MAX-ACCESS read-only
			STATUS current
			DESCRIPTION
				"Serial number"
		::= { hap3000c01v1Entry 175 }

		-- 1.3.6.1.4.1.10106.3.382502
		hap3000c01v2 OBJECT IDENTIFIER ::= { albalaProducts 382502 }

		-- 1.3.6.1.4.1.10106.3.382502.1
		hap3000c01v2Table  OBJECT-TYPE
			SYNTAX SEQUENCE OF Hap3000c01v2Entry
			MAX-ACCESS not-accessible
			STATUS current
			DESCRIPTION
				"Module  HAP3000C01V2 Table"
			::= { hap3000c01v2 1 }

		-- 1.3.6.1.4.1.10106.3.382502.1.1
		hap3000c01v2Entry  OBJECT-TYPE
			SYNTAX Hap3000c01v2Entry
			MAX-ACCESS not-accessible
			STATUS current
			DESCRIPTION
				"Module HAP3000C01V2 Entry"
			INDEX { hap3000c01v2Index }
			::= { hap3000c01v2Table 1 }

			Hap3000c01v2Entry ::=
			SEQUENCE {
				hap3000c01v2Index
				ModuleIndex,
				hap3000c01v2ActivePreset
				Preset16Active,
				hap3000c01v2LoadPreset
				Preset16Load,
				hap3000c01v2SavePreset
				Preset16Save,
				hap3000c01v2SynchroMode
				Bit0Fra1Lin,
				hap3000c01v2FailMode
				Bit0Fre1Blk,
				hap3000c01v2DelayMode
				Bit0Syn1De2,
				hap3000c01v2HDelay
				DelayPixel5,
				hap3000c01v2FrameDelay
				DelayFram4,
				hap3000c01v2VDelay
				DelayLines2,
				hap3000c01v2Grp12Mult
				MultichannlSel,
				hap3000c01v2Grp34Mult
				MultichannlSel,
				hap3000c01v2Grp1P0Mode
				Bit0Ste1Mon,
				hap3000c01v2Grp1P1Mode
				Bit0Ste1Mon,
				hap3000c01v2Grp2P0Mode
				Bit0Ste1Mon,
				hap3000c01v2Grp2P1Mode
				Bit0Ste1Mon,
				hap3000c01v2Grp3P0Mode
				Bit0Ste1Mon,
				hap3000c01v2Grp3P1Mode
				Bit0Ste1Mon,
				hap3000c01v2Grp4P0Mode
				Bit0Ste1Mon,
				hap3000c01v2Grp4P1Mode
				Bit0Ste1Mon,
				hap3000c01v2ProcessingG1p0
				Bit0Dis1Ena,
				hap3000c01v2ProcessingG1p1
				Bit0Dis1Ena,
				hap3000c01v2ProcessingG2p0
				Bit0Dis1Ena,
				hap3000c01v2ProcessingG2p1
				Bit0Dis1Ena,
				hap3000c01v2ProcessingG3p0
				Bit0Dis1Ena,
				hap3000c01v2ProcessingG3p1
				Bit0Dis1Ena,
				hap3000c01v2ProcessingG4p0
				Bit0Dis1Ena,
				hap3000c01v2ProcessingG4p1
				Bit0Dis1Ena,
				hap3000c01v2LimiterG1p0
				BitMask,
				hap3000c01v2LimiterG1p1
				BitMask,
				hap3000c01v2LimiterG2p0
				BitMask,
				hap3000c01v2LimiterG2p1
				BitMask,
				hap3000c01v2LimiterG3p0
				BitMask,
				hap3000c01v2LimiterG3p1
				BitMask,
				hap3000c01v2LimiterG4p0
				BitMask,
				hap3000c01v2LimiterG4p1
				BitMask,
				hap3000c01v2TransientG1p0
				BitMask,
				hap3000c01v2TransientG1p1
				BitMask,
				hap3000c01v2TransientG2p0
				BitMask,
				hap3000c01v2TransientG2p1
				BitMask,
				hap3000c01v2TransientG3p0
				BitMask,
				hap3000c01v2TransientG3p1
				BitMask,
				hap3000c01v2TransientG4p0
				BitMask,
				hap3000c01v2TransientG4p1
				BitMask,
				hap3000c01v2LoudnessG1p0
				BitMask,
				hap3000c01v2LoudnessG1p1
				BitMask,
				hap3000c01v2LoudnessG2p0
				BitMask,
				hap3000c01v2LoudnessG2p1
				BitMask,
				hap3000c01v2LoudnessG3p0
				BitMask,
				hap3000c01v2LoudnessG3p1
				BitMask,
				hap3000c01v2LoudnessG4p0
				BitMask,
				hap3000c01v2LoudnessG4p1
				BitMask,
				hap3000c01v2LoudTarg
				LevelLkfs2,
				hap3000c01v2TruePeakMax
				LevelDbfs8,
				hap3000c01v2Grp1P0A
				AudioMxInput5,
				hap3000c01v2Grp1P1A
				AudioMxInput5,
				hap3000c01v2Grp2P0A
				AudioMxInput5,
				hap3000c01v2Grp2P1A
				AudioMxInput5,
				hap3000c01v2Grp3P0A
				AudioMxInput5,
				hap3000c01v2Grp3P1A
				AudioMxInput5,
				hap3000c01v2Grp4P0A
				AudioMxInput5,
				hap3000c01v2Grp4P1A
				AudioMxInput5,
				hap3000c01v2MeasPlace
				Bit0In1Out,
				hap3000c01v2SelLoudMeas
				LoudnessType,
				hap3000c01v2StatMeas
				Bit0LdBit1Pk,
				hap3000c01v2OsdEnable
				Bit0Dis1Ena,
				hap3000c01v2DispPeak
				Bit0Dis1Ena,
				hap3000c01v2DispLoudness
				Bit0Dis1Ena,
				hap3000c01v2Meter1
				BitMask,
				hap3000c01v2Meter2
				BitMask,
				hap3000c01v2Meter3
				BitMask,
				hap3000c01v2Meter4
				BitMask,
				hap3000c01v2Meter5
				BitMask,
				hap3000c01v2Meter6
				BitMask,
				hap3000c01v2Meter7
				BitMask,
				hap3000c01v2Meter8
				BitMask,
				hap3000c01v2DispMode
				PpmDistrib,
				hap3000c01v2StatFlash
				BitFailN,
				hap3000c01v2NoSig
				BitFail,
				hap3000c01v2NoSigTrapEnable
				AlarmEnable,
				hap3000c01v2Unlock
				BitFail,
				hap3000c01v2UnlockTrapEnable
				AlarmEnable,
				hap3000c01v2EdhCrc
				BitFail,
				hap3000c01v2EdhCrcTrapEnable
				AlarmEnable,
				hap3000c01v2NoRef
				BitFail,
				hap3000c01v2NoRefTrapEnable
				AlarmEnable,
				hap3000c01v2RefUnlck
				BitFail,
				hap3000c01v2RefUnlckTrapEnable
				AlarmEnable,
				hap3000c01v2AudioFail
				BitFail,
				hap3000c01v2AudioFailTrapEnable
				AlarmEnable,
				hap3000c01v2FormatIn
				SdiHd3gFmt3,
				hap3000c01v2FormatRef
				SdiHd3gFmt3,
				hap3000c01v2SigDelay
				DelayX20Us,
				hap3000c01v2SerialNo
				SerialNo
			 }

		-- 1.3.6.1.4.1.10106.3.101291.1.1.1
		hap3000c01v2Index OBJECT-TYPE
			SYNTAX ModuleIndex
			MAX-ACCESS read-only
			STATUS current
			DESCRIPTION
				"Index of HAP3000C01V2 Table"
		::= { hap3000c01v2Entry 1 }

		-- 1.3.6.1.4.1.10106.3.101291.1.1.3
		hap3000c01v2ActivePreset OBJECT-TYPE
			SYNTAX Preset16Active
			MAX-ACCESS read-only
			STATUS current
			DESCRIPTION
				"Shows the active preset"
		::= { hap3000c01v2Entry 3 }

		-- 1.3.6.1.4.1.10106.3.101291.1.1.5
		hap3000c01v2LoadPreset OBJECT-TYPE
			SYNTAX Preset16Load
			MAX-ACCESS read-write
			STATUS current
			DESCRIPTION
				"Allows loading a preset"
		::= { hap3000c01v2Entry 5 }

		-- 1.3.6.1.4.1.10106.3.101291.1.1.7
		hap3000c01v2SavePreset OBJECT-TYPE
			SYNTAX Preset16Save
			MAX-ACCESS read-write
			STATUS current
			DESCRIPTION
				"Allows saving a preset"
		::= { hap3000c01v2Entry 7 }

		-- 1.3.6.1.4.1.10106.3.101291.1.1.9
		hap3000c01v2SynchroMode OBJECT-TYPE
			SYNTAX Bit0Fra1Lin
			MAX-ACCESS read-write
			STATUS current
			DESCRIPTION
				"Allows selecting the synchronizing mode"
		::= { hap3000c01v2Entry 9 }

		-- 1.3.6.1.4.1.10106.3.101291.1.1.11
		hap3000c01v2FailMode OBJECT-TYPE
			SYNTAX Bit0Fre1Blk
			MAX-ACCESS read-write
			STATUS current
			DESCRIPTION
				"Allows selecting the output video signal if the input fails"
		::= { hap3000c01v2Entry 11 }

		-- 1.3.6.1.4.1.10106.3.101291.1.1.13
		hap3000c01v2DelayMode OBJECT-TYPE
			SYNTAX Bit0Syn1De2
			MAX-ACCESS read-write
			STATUS current
			DESCRIPTION
				"Allows selecting the operating mode"
		::= { hap3000c01v2Entry 13 }

		-- 1.3.6.1.4.1.10106.3.101291.1.1.15
		hap3000c01v2HDelay OBJECT-TYPE
			SYNTAX DelayPixel5
			MAX-ACCESS read-write
			STATUS current
			DESCRIPTION
				"Allows adjusting the video horizontal delay"
		::= { hap3000c01v2Entry 15 }

		-- 1.3.6.1.4.1.10106.3.101291.1.1.17
		hap3000c01v2FrameDelay OBJECT-TYPE
			SYNTAX DelayFram4
			MAX-ACCESS read-write
			STATUS current
			DESCRIPTION
				"Allows adjusting the frame delay"
		::= { hap3000c01v2Entry 17 }

		-- 1.3.6.1.4.1.10106.3.101291.1.1.19
		hap3000c01v2VDelay OBJECT-TYPE
			SYNTAX DelayLines2
			MAX-ACCESS read-write
			STATUS current
			DESCRIPTION
				"Allows adjusting the video vertical delay"
		::= { hap3000c01v2Entry 19 }

		-- 1.3.6.1.4.1.10106.3.101291.1.1.21
		hap3000c01v2Grp12Mult OBJECT-TYPE
			SYNTAX MultichannlSel
			MAX-ACCESS read-write
			STATUS current
			DESCRIPTION
				"Allows selecting multichannel audio in groups 1 and 2: Multichannel_A: mapping at G1P0"
		::= { hap3000c01v2Entry 21 }

		-- 1.3.6.1.4.1.10106.3.101291.1.1.23
		hap3000c01v2Grp34Mult OBJECT-TYPE
			SYNTAX MultichannlSel
			MAX-ACCESS read-write
			STATUS current
			DESCRIPTION
				"Allows selecting multichannel audio in groups 3 and 4: Multichannel_A: mapping at G3P0"
		::= { hap3000c01v2Entry 23 }

		-- 1.3.6.1.4.1.10106.3.101291.1.1.25
		hap3000c01v2Grp1P0Mode OBJECT-TYPE
			SYNTAX Bit0Ste1Mon
			MAX-ACCESS read-write
			STATUS current
			DESCRIPTION
				"Allows selecting audio type in group 1 pair 0"
		::= { hap3000c01v2Entry 25 }

		-- 1.3.6.1.4.1.10106.3.101291.1.1.27
		hap3000c01v2Grp1P1Mode OBJECT-TYPE
			SYNTAX Bit0Ste1Mon
			MAX-ACCESS read-write
			STATUS current
			DESCRIPTION
				"Allows selecting audio type in group 1 pair 1"
		::= { hap3000c01v2Entry 27 }

		-- 1.3.6.1.4.1.10106.3.101291.1.1.29
		hap3000c01v2Grp2P0Mode OBJECT-TYPE
			SYNTAX Bit0Ste1Mon
			MAX-ACCESS read-write
			STATUS current
			DESCRIPTION
				"Allows selecting audio type in group 2 pair 0"
		::= { hap3000c01v2Entry 29 }

		-- 1.3.6.1.4.1.10106.3.101291.1.1.31
		hap3000c01v2Grp2P1Mode OBJECT-TYPE
			SYNTAX Bit0Ste1Mon
			MAX-ACCESS read-write
			STATUS current
			DESCRIPTION
				"Allows selecting audio type in group 2 pair 1"
		::= { hap3000c01v2Entry 31 }

		-- 1.3.6.1.4.1.10106.3.101291.1.1.33
		hap3000c01v2Grp3P0Mode OBJECT-TYPE
			SYNTAX Bit0Ste1Mon
			MAX-ACCESS read-write
			STATUS current
			DESCRIPTION
				"Allows selecting audio type in group 3 pair 0"
		::= { hap3000c01v2Entry 33 }

		-- 1.3.6.1.4.1.10106.3.101291.1.1.35
		hap3000c01v2Grp3P1Mode OBJECT-TYPE
			SYNTAX Bit0Ste1Mon
			MAX-ACCESS read-write
			STATUS current
			DESCRIPTION
				"Allows selecting audio type in group 3 pair 1"
		::= { hap3000c01v2Entry 35 }

		-- 1.3.6.1.4.1.10106.3.101291.1.1.37
		hap3000c01v2Grp4P0Mode OBJECT-TYPE
			SYNTAX Bit0Ste1Mon
			MAX-ACCESS read-write
			STATUS current
			DESCRIPTION
				"Allows selecting audio type in group 4 pair 0"
		::= { hap3000c01v2Entry 37 }

		-- 1.3.6.1.4.1.10106.3.101291.1.1.39
		hap3000c01v2Grp4P1Mode OBJECT-TYPE
			SYNTAX Bit0Ste1Mon
			MAX-ACCESS read-write
			STATUS current
			DESCRIPTION
				"Allows selecting audio type in group 4 pair 1"
		::= { hap3000c01v2Entry 39 }

		-- 1.3.6.1.4.1.10106.3.101291.1.1.41
		hap3000c01v2ProcessingG1p0 OBJECT-TYPE
			SYNTAX Bit0Dis1Ena
			MAX-ACCESS read-write
			STATUS current
			DESCRIPTION
				"Allows processing the audio in group 1 pair 0"
		::= { hap3000c01v2Entry 41 }

		-- 1.3.6.1.4.1.10106.3.101291.1.1.43
		hap3000c01v2ProcessingG1p1 OBJECT-TYPE
			SYNTAX Bit0Dis1Ena
			MAX-ACCESS read-write
			STATUS current
			DESCRIPTION
				"Allows processing the audio in group 1 pair 1"
		::= { hap3000c01v2Entry 43 }

		-- 1.3.6.1.4.1.10106.3.101291.1.1.45
		hap3000c01v2ProcessingG2p0 OBJECT-TYPE
			SYNTAX Bit0Dis1Ena
			MAX-ACCESS read-write
			STATUS current
			DESCRIPTION
				"Allows processing the audio in group 2 pair 0"
		::= { hap3000c01v2Entry 45 }

		-- 1.3.6.1.4.1.10106.3.101291.1.1.47
		hap3000c01v2ProcessingG2p1 OBJECT-TYPE
			SYNTAX Bit0Dis1Ena
			MAX-ACCESS read-write
			STATUS current
			DESCRIPTION
				"Allows processing the audio in group 2 pair 1"
		::= { hap3000c01v2Entry 47 }

		-- 1.3.6.1.4.1.10106.3.101291.1.1.49
		hap3000c01v2ProcessingG3p0 OBJECT-TYPE
			SYNTAX Bit0Dis1Ena
			MAX-ACCESS read-write
			STATUS current
			DESCRIPTION
				"Allows processing the audio in group 3 pair 0"
		::= { hap3000c01v2Entry 49 }

		-- 1.3.6.1.4.1.10106.3.101291.1.1.51
		hap3000c01v2ProcessingG3p1 OBJECT-TYPE
			SYNTAX Bit0Dis1Ena
			MAX-ACCESS read-write
			STATUS current
			DESCRIPTION
				"Allows processing the audio in group 3 pair 1"
		::= { hap3000c01v2Entry 51 }

		-- 1.3.6.1.4.1.10106.3.101291.1.1.53
		hap3000c01v2ProcessingG4p0 OBJECT-TYPE
			SYNTAX Bit0Dis1Ena
			MAX-ACCESS read-write
			STATUS current
			DESCRIPTION
				"Allows processing the audio in group 4 pair 0"
		::= { hap3000c01v2Entry 53 }

		-- 1.3.6.1.4.1.10106.3.101291.1.1.55
		hap3000c01v2ProcessingG4p1 OBJECT-TYPE
			SYNTAX Bit0Dis1Ena
			MAX-ACCESS read-write
			STATUS current
			DESCRIPTION
				"Allows processing the audio in group 4 pair 1"
		::= { hap3000c01v2Entry 55 }

		-- 1.3.6.1.4.1.10106.3.101291.1.1.57
		hap3000c01v2LimiterG1p0 OBJECT-TYPE
			SYNTAX BitMask
			MAX-ACCESS read-write
			STATUS current
			DESCRIPTION
				"Enables the peak limiter for group 1 pair 0"
		::= { hap3000c01v2Entry 57 }

		-- 1.3.6.1.4.1.10106.3.101291.1.1.59
		hap3000c01v2LimiterG1p1 OBJECT-TYPE
			SYNTAX BitMask
			MAX-ACCESS read-write
			STATUS current
			DESCRIPTION
				"Enables the peak limiter for group 1 pair 1"
		::= { hap3000c01v2Entry 59 }

		-- 1.3.6.1.4.1.10106.3.101291.1.1.61
		hap3000c01v2LimiterG2p0 OBJECT-TYPE
			SYNTAX BitMask
			MAX-ACCESS read-write
			STATUS current
			DESCRIPTION
				"Enables the peak limiter for group 2 pair 0"
		::= { hap3000c01v2Entry 61 }

		-- 1.3.6.1.4.1.10106.3.101291.1.1.63
		hap3000c01v2LimiterG2p1 OBJECT-TYPE
			SYNTAX BitMask
			MAX-ACCESS read-write
			STATUS current
			DESCRIPTION
				"Enables the peak limiter for group 2 pair 1"
		::= { hap3000c01v2Entry 63 }

		-- 1.3.6.1.4.1.10106.3.101291.1.1.65
		hap3000c01v2LimiterG3p0 OBJECT-TYPE
			SYNTAX BitMask
			MAX-ACCESS read-write
			STATUS current
			DESCRIPTION
				"Enables the peak limiter for group 3 pair 0"
		::= { hap3000c01v2Entry 65 }

		-- 1.3.6.1.4.1.10106.3.101291.1.1.67
		hap3000c01v2LimiterG3p1 OBJECT-TYPE
			SYNTAX BitMask
			MAX-ACCESS read-write
			STATUS current
			DESCRIPTION
				"Enables the peak limiter for group 3 pair 1"
		::= { hap3000c01v2Entry 67 }

		-- 1.3.6.1.4.1.10106.3.101291.1.1.69
		hap3000c01v2LimiterG4p0 OBJECT-TYPE
			SYNTAX BitMask
			MAX-ACCESS read-write
			STATUS current
			DESCRIPTION
				"Enables the peak limiter for group 4 pair 0"
		::= { hap3000c01v2Entry 69 }

		-- 1.3.6.1.4.1.10106.3.101291.1.1.71
		hap3000c01v2LimiterG4p1 OBJECT-TYPE
			SYNTAX BitMask
			MAX-ACCESS read-write
			STATUS current
			DESCRIPTION
				"Enables the peak limiter for group 4 pair 1"
		::= { hap3000c01v2Entry 71 }

		-- 1.3.6.1.4.1.10106.3.101291.1.1.73
		hap3000c01v2TransientG1p0 OBJECT-TYPE
			SYNTAX BitMask
			MAX-ACCESS read-write
			STATUS current
			DESCRIPTION
				"Enables the transient processing for group 1 pair 0"
		::= { hap3000c01v2Entry 73 }

		-- 1.3.6.1.4.1.10106.3.101291.1.1.75
		hap3000c01v2TransientG1p1 OBJECT-TYPE
			SYNTAX BitMask
			MAX-ACCESS read-write
			STATUS current
			DESCRIPTION
				"Enables the transient processing for group 1 pair 1"
		::= { hap3000c01v2Entry 75 }

		-- 1.3.6.1.4.1.10106.3.101291.1.1.77
		hap3000c01v2TransientG2p0 OBJECT-TYPE
			SYNTAX BitMask
			MAX-ACCESS read-write
			STATUS current
			DESCRIPTION
				"Enables the transient processing for group 2 pair 0"
		::= { hap3000c01v2Entry 77 }

		-- 1.3.6.1.4.1.10106.3.101291.1.1.79
		hap3000c01v2TransientG2p1 OBJECT-TYPE
			SYNTAX BitMask
			MAX-ACCESS read-write
			STATUS current
			DESCRIPTION
				"Enables the transient processing for group 2 pair 1"
		::= { hap3000c01v2Entry 79 }

		-- 1.3.6.1.4.1.10106.3.101291.1.1.81
		hap3000c01v2TransientG3p0 OBJECT-TYPE
			SYNTAX BitMask
			MAX-ACCESS read-write
			STATUS current
			DESCRIPTION
				"Enables the transient processing for group 3 pair 0"
		::= { hap3000c01v2Entry 81 }

		-- 1.3.6.1.4.1.10106.3.101291.1.1.83
		hap3000c01v2TransientG3p1 OBJECT-TYPE
			SYNTAX BitMask
			MAX-ACCESS read-write
			STATUS current
			DESCRIPTION
				"Enables the transient processing for group 3 pair 1"
		::= { hap3000c01v2Entry 83 }

		-- 1.3.6.1.4.1.10106.3.101291.1.1.85
		hap3000c01v2TransientG4p0 OBJECT-TYPE
			SYNTAX BitMask
			MAX-ACCESS read-write
			STATUS current
			DESCRIPTION
				"Enables the transient processing for group 4 pair 0"
		::= { hap3000c01v2Entry 85 }

		-- 1.3.6.1.4.1.10106.3.101291.1.1.87
		hap3000c01v2TransientG4p1 OBJECT-TYPE
			SYNTAX BitMask
			MAX-ACCESS read-write
			STATUS current
			DESCRIPTION
				"Enables the transient processing for group 4 pair 1"
		::= { hap3000c01v2Entry 87 }

		-- 1.3.6.1.4.1.10106.3.101291.1.1.89
		hap3000c01v2LoudnessG1p0 OBJECT-TYPE
			SYNTAX BitMask
			MAX-ACCESS read-write
			STATUS current
			DESCRIPTION
				"Enables the loudness normalizer for group 1 pair 0"
		::= { hap3000c01v2Entry 89 }

		-- 1.3.6.1.4.1.10106.3.101291.1.1.91
		hap3000c01v2LoudnessG1p1 OBJECT-TYPE
			SYNTAX BitMask
			MAX-ACCESS read-write
			STATUS current
			DESCRIPTION
				"Enables the loudness normalizer for group 1 pair 1"
		::= { hap3000c01v2Entry 91 }

		-- 1.3.6.1.4.1.10106.3.101291.1.1.93
		hap3000c01v2LoudnessG2p0 OBJECT-TYPE
			SYNTAX BitMask
			MAX-ACCESS read-write
			STATUS current
			DESCRIPTION
				"Enables the loudness normalizer for group 2 pair 0"
		::= { hap3000c01v2Entry 93 }

		-- 1.3.6.1.4.1.10106.3.101291.1.1.95
		hap3000c01v2LoudnessG2p1 OBJECT-TYPE
			SYNTAX BitMask
			MAX-ACCESS read-write
			STATUS current
			DESCRIPTION
				"Enables the loudness normalizer for group 2 pair 1"
		::= { hap3000c01v2Entry 95 }

		-- 1.3.6.1.4.1.10106.3.101291.1.1.97
		hap3000c01v2LoudnessG3p0 OBJECT-TYPE
			SYNTAX BitMask
			MAX-ACCESS read-write
			STATUS current
			DESCRIPTION
				"Enables the loudness normalizer for group 3 pair 0"
		::= { hap3000c01v2Entry 97 }

		-- 1.3.6.1.4.1.10106.3.101291.1.1.99
		hap3000c01v2LoudnessG3p1 OBJECT-TYPE
			SYNTAX BitMask
			MAX-ACCESS read-write
			STATUS current
			DESCRIPTION
				"Enables the loudness normalizer for group 3 pair 1"
		::= { hap3000c01v2Entry 99 }

		-- 1.3.6.1.4.1.10106.3.101291.1.1.101
		hap3000c01v2LoudnessG4p0 OBJECT-TYPE
			SYNTAX BitMask
			MAX-ACCESS read-write
			STATUS current
			DESCRIPTION
				"Enables the loudness normalizer for group 4 pair 0"
		::= { hap3000c01v2Entry 101 }

		-- 1.3.6.1.4.1.10106.3.101291.1.1.103
		hap3000c01v2LoudnessG4p1 OBJECT-TYPE
			SYNTAX BitMask
			MAX-ACCESS read-write
			STATUS current
			DESCRIPTION
				"Enables the loudness normalizer for group 4 pair 1"
		::= { hap3000c01v2Entry 103 }

		-- 1.3.6.1.4.1.10106.3.101291.1.1.105
		hap3000c01v2LoudTarg OBJECT-TYPE
			SYNTAX LevelLkfs2
			MAX-ACCESS read-write
			STATUS current
			DESCRIPTION
				"Integral loudness target"
		::= { hap3000c01v2Entry 105 }

		-- 1.3.6.1.4.1.10106.3.101291.1.1.107
		hap3000c01v2TruePeakMax OBJECT-TYPE
			SYNTAX LevelDbfs8
			MAX-ACCESS read-write
			STATUS current
			DESCRIPTION
				"Maximum level for the audio signal true peak"
		::= { hap3000c01v2Entry 107 }

		-- 1.3.6.1.4.1.10106.3.101291.1.1.109
		hap3000c01v2Grp1P0A OBJECT-TYPE
			SYNTAX AudioMxInput5
			MAX-ACCESS read-write
			STATUS current
			DESCRIPTION
				"Allows selecting the audio embedded in group 1 pair 0"
		::= { hap3000c01v2Entry 109 }

		-- 1.3.6.1.4.1.10106.3.101291.1.1.111
		hap3000c01v2Grp1P1A OBJECT-TYPE
			SYNTAX AudioMxInput5
			MAX-ACCESS read-write
			STATUS current
			DESCRIPTION
				"Allows selecting the audio embedded in group 1 pair 1"
		::= { hap3000c01v2Entry 111 }

		-- 1.3.6.1.4.1.10106.3.101291.1.1.113
		hap3000c01v2Grp2P0A OBJECT-TYPE
			SYNTAX AudioMxInput5
			MAX-ACCESS read-write
			STATUS current
			DESCRIPTION
				"Allows selecting the audio embedded in group 2 pair 0"
		::= { hap3000c01v2Entry 113 }

		-- 1.3.6.1.4.1.10106.3.101291.1.1.115
		hap3000c01v2Grp2P1A OBJECT-TYPE
			SYNTAX AudioMxInput5
			MAX-ACCESS read-write
			STATUS current
			DESCRIPTION
				"Allows selecting the audio embedded in group 2 pair 1"
		::= { hap3000c01v2Entry 115 }

		-- 1.3.6.1.4.1.10106.3.101291.1.1.117
		hap3000c01v2Grp3P0A OBJECT-TYPE
			SYNTAX AudioMxInput5
			MAX-ACCESS read-write
			STATUS current
			DESCRIPTION
				"Allows selecting the audio embedded in group 3 pair 0"
		::= { hap3000c01v2Entry 117 }

		-- 1.3.6.1.4.1.10106.3.101291.1.1.119
		hap3000c01v2Grp3P1A OBJECT-TYPE
			SYNTAX AudioMxInput5
			MAX-ACCESS read-write
			STATUS current
			DESCRIPTION
				"Allows selecting the audio embedded in group 3 pair 1"
		::= { hap3000c01v2Entry 119 }

		-- 1.3.6.1.4.1.10106.3.101291.1.1.121
		hap3000c01v2Grp4P0A OBJECT-TYPE
			SYNTAX AudioMxInput5
			MAX-ACCESS read-write
			STATUS current
			DESCRIPTION
				"Allows selecting the audio embedded in group 4 pair 0"
		::= { hap3000c01v2Entry 121 }

		-- 1.3.6.1.4.1.10106.3.101291.1.1.123
		hap3000c01v2Grp4P1A OBJECT-TYPE
			SYNTAX AudioMxInput5
			MAX-ACCESS read-write
			STATUS current
			DESCRIPTION
				"Allows selecting the audio embedded in group 4 pair 1"
		::= { hap3000c01v2Entry 123 }

		-- 1.3.6.1.4.1.10106.3.101291.1.1.125
		hap3000c01v2MeasPlace OBJECT-TYPE
			SYNTAX Bit0In1Out
			MAX-ACCESS read-write
			STATUS current
			DESCRIPTION
				"Allows selecting the point in which the measure is performed"
		::= { hap3000c01v2Entry 125 }

		-- 1.3.6.1.4.1.10106.3.101291.1.1.127
		hap3000c01v2SelLoudMeas OBJECT-TYPE
			SYNTAX LoudnessType
			MAX-ACCESS read-write
			STATUS current
			DESCRIPTION
				"Allows selecting the kind of loudness measure to be displayed"
		::= { hap3000c01v2Entry 127 }

		-- 1.3.6.1.4.1.10106.3.101291.1.1.129
		hap3000c01v2StatMeas OBJECT-TYPE
			SYNTAX Bit0LdBit1Pk
			MAX-ACCESS read-write
			STATUS current
			DESCRIPTION
				"Allows selecting the kind of measure to be displayed in the state registers"
		::= { hap3000c01v2Entry 129 }

		-- 1.3.6.1.4.1.10106.3.101291.1.1.131
		hap3000c01v2OsdEnable OBJECT-TYPE
			SYNTAX Bit0Dis1Ena
			MAX-ACCESS read-write
			STATUS current
			DESCRIPTION
				"Enables the On Screen Display"
		::= { hap3000c01v2Entry 131 }

		-- 1.3.6.1.4.1.10106.3.101291.1.1.133
		hap3000c01v2DispPeak OBJECT-TYPE
			SYNTAX Bit0Dis1Ena
			MAX-ACCESS read-write
			STATUS current
			DESCRIPTION
				"Enables the peak represesntation on the OSD"
		::= { hap3000c01v2Entry 133 }

		-- 1.3.6.1.4.1.10106.3.101291.1.1.135
		hap3000c01v2DispLoudness OBJECT-TYPE
			SYNTAX Bit0Dis1Ena
			MAX-ACCESS read-write
			STATUS current
			DESCRIPTION
				"Enables the loudness representation on the OSD"
		::= { hap3000c01v2Entry 135 }

		-- 1.3.6.1.4.1.10106.3.101291.1.1.137
		hap3000c01v2Meter1 OBJECT-TYPE
			SYNTAX BitMask
			MAX-ACCESS read-write
			STATUS current
			DESCRIPTION
				"Displays the meter G1P0 on the OSD"
		::= { hap3000c01v2Entry 137 }

		-- 1.3.6.1.4.1.10106.3.101291.1.1.139
		hap3000c01v2Meter2 OBJECT-TYPE
			SYNTAX BitMask
			MAX-ACCESS read-write
			STATUS current
			DESCRIPTION
				"Displays the meter G1P1 on the OSD"
		::= { hap3000c01v2Entry 139 }

		-- 1.3.6.1.4.1.10106.3.101291.1.1.141
		hap3000c01v2Meter3 OBJECT-TYPE
			SYNTAX BitMask
			MAX-ACCESS read-write
			STATUS current
			DESCRIPTION
				"Displays the meter G2P0 on the OSD"
		::= { hap3000c01v2Entry 141 }

		-- 1.3.6.1.4.1.10106.3.101291.1.1.143
		hap3000c01v2Meter4 OBJECT-TYPE
			SYNTAX BitMask
			MAX-ACCESS read-write
			STATUS current
			DESCRIPTION
				"Displays the meter G2P1 on the OSD"
		::= { hap3000c01v2Entry 143 }

		-- 1.3.6.1.4.1.10106.3.101291.1.1.145
		hap3000c01v2Meter5 OBJECT-TYPE
			SYNTAX BitMask
			MAX-ACCESS read-write
			STATUS current
			DESCRIPTION
				"Displays the meter G3P0 on the OSD"
		::= { hap3000c01v2Entry 145 }

		-- 1.3.6.1.4.1.10106.3.101291.1.1.147
		hap3000c01v2Meter6 OBJECT-TYPE
			SYNTAX BitMask
			MAX-ACCESS read-write
			STATUS current
			DESCRIPTION
				"Displays the meter G3P1 on the OSD"
		::= { hap3000c01v2Entry 147 }

		-- 1.3.6.1.4.1.10106.3.101291.1.1.149
		hap3000c01v2Meter7 OBJECT-TYPE
			SYNTAX BitMask
			MAX-ACCESS read-write
			STATUS current
			DESCRIPTION
				"Displays the meter G4P0 on the OSD"
		::= { hap3000c01v2Entry 149 }

		-- 1.3.6.1.4.1.10106.3.101291.1.1.151
		hap3000c01v2Meter8 OBJECT-TYPE
			SYNTAX BitMask
			MAX-ACCESS read-write
			STATUS current
			DESCRIPTION
				"Displays the meter G4P1 on the OSD"
		::= { hap3000c01v2Entry 151 }

		-- 1.3.6.1.4.1.10106.3.101291.1.1.153
		hap3000c01v2DispMode OBJECT-TYPE
			SYNTAX PpmDistrib
			MAX-ACCESS read-write
			STATUS current
			DESCRIPTION
				"Allows selecting the PPMs distribution: 1 rpw or 2 rows"
		::= { hap3000c01v2Entry 153 }

		-- 1.3.6.1.4.1.10106.3.101291.1.1.155
		hap3000c01v2StatFlash OBJECT-TYPE
			SYNTAX BitFailN
			MAX-ACCESS read-only
			STATUS current
			DESCRIPTION
				"Displays the Flash state"
		::= { hap3000c01v2Entry 155 }

		-- 1.3.6.1.4.1.10106.3.101291.1.1.157
		hap3000c01v2NoSig OBJECT-TYPE
			SYNTAX BitFail
			MAX-ACCESS read-only
			STATUS current
			DESCRIPTION
				"No SDI signal fail"
		::= { hap3000c01v2Entry 157 }

		-- 1.3.6.1.4.1.10106.3.101291.1.1.158
		hap3000c01v2NoSigTrapEnable OBJECT-TYPE
			SYNTAX AlarmEnable
			MAX-ACCESS read-write
			STATUS current
			DESCRIPTION
				"No SDI signal fail Trap Enable"
		::= { hap3000c01v2Entry 158 }

		-- 1.3.6.1.4.1.10106.3.101291.1.1.159
		hap3000c01v2Unlock OBJECT-TYPE
			SYNTAX BitFail
			MAX-ACCESS read-only
			STATUS current
			DESCRIPTION
				"Unlock fail"
		::= { hap3000c01v2Entry 159 }

		-- 1.3.6.1.4.1.10106.3.101291.1.1.160
		hap3000c01v2UnlockTrapEnable OBJECT-TYPE
			SYNTAX AlarmEnable
			MAX-ACCESS read-write
			STATUS current
			DESCRIPTION
				"Unlock fail Trap Enable"
		::= { hap3000c01v2Entry 160 }

		-- 1.3.6.1.4.1.10106.3.101291.1.1.161
		hap3000c01v2EdhCrc OBJECT-TYPE
			SYNTAX BitFail
			MAX-ACCESS read-only
			STATUS current
			DESCRIPTION
				"EDH/CRC errors"
		::= { hap3000c01v2Entry 161 }

		-- 1.3.6.1.4.1.10106.3.101291.1.1.162
		hap3000c01v2EdhCrcTrapEnable OBJECT-TYPE
			SYNTAX AlarmEnable
			MAX-ACCESS read-write
			STATUS current
			DESCRIPTION
				"EDH/CRC errors Trap Enable"
		::= { hap3000c01v2Entry 162 }

		-- 1.3.6.1.4.1.10106.3.101291.1.1.163
		hap3000c01v2NoRef OBJECT-TYPE
			SYNTAX BitFail
			MAX-ACCESS read-only
			STATUS current
			DESCRIPTION
				"No reference signal fail"
		::= { hap3000c01v2Entry 163 }

		-- 1.3.6.1.4.1.10106.3.101291.1.1.164
		hap3000c01v2NoRefTrapEnable OBJECT-TYPE
			SYNTAX AlarmEnable
			MAX-ACCESS read-write
			STATUS current
			DESCRIPTION
				"No reference signal fail Trap Enable"
		::= { hap3000c01v2Entry 164 }

		-- 1.3.6.1.4.1.10106.3.101291.1.1.165
		hap3000c01v2RefUnlck OBJECT-TYPE
			SYNTAX BitFail
			MAX-ACCESS read-only
			STATUS current
			DESCRIPTION
				"Reference input unlock fail"
		::= { hap3000c01v2Entry 165 }

		-- 1.3.6.1.4.1.10106.3.101291.1.1.166
		hap3000c01v2RefUnlckTrapEnable OBJECT-TYPE
			SYNTAX AlarmEnable
			MAX-ACCESS read-write
			STATUS current
			DESCRIPTION
				"Reference input unlock fail Trap Enable"
		::= { hap3000c01v2Entry 166 }

		-- 1.3.6.1.4.1.10106.3.101291.1.1.167
		hap3000c01v2AudioFail OBJECT-TYPE
			SYNTAX BitFail
			MAX-ACCESS read-only
			STATUS current
			DESCRIPTION
				"Audio fail"
		::= { hap3000c01v2Entry 167 }

		-- 1.3.6.1.4.1.10106.3.101291.1.1.168
		hap3000c01v2AudioFailTrapEnable OBJECT-TYPE
			SYNTAX AlarmEnable
			MAX-ACCESS read-write
			STATUS current
			DESCRIPTION
				"Audio fail Trap Enable"
		::= { hap3000c01v2Entry 168 }

		-- 1.3.6.1.4.1.10106.3.101291.1.1.169
		hap3000c01v2FormatIn OBJECT-TYPE
			SYNTAX SdiHd3gFmt3
			MAX-ACCESS read-only
			STATUS current
			DESCRIPTION
				"Indicates the SDI transmited signal format"
		::= { hap3000c01v2Entry 169 }

		-- 1.3.6.1.4.1.10106.3.101291.1.1.171
		hap3000c01v2FormatRef OBJECT-TYPE
			SYNTAX SdiHd3gFmt3
			MAX-ACCESS read-only
			STATUS current
			DESCRIPTION
				"Indicates the reference SDI signal format"
		::= { hap3000c01v2Entry 171 }

		-- 1.3.6.1.4.1.10106.3.101291.1.1.173
		hap3000c01v2SigDelay OBJECT-TYPE
			SYNTAX DelayX20Us
			MAX-ACCESS read-only
			STATUS current
			DESCRIPTION
				"Indicates the input to output delay"
		::= { hap3000c01v2Entry 173 }

		-- 1.3.6.1.4.1.10106.3.101291.1.1.175
		hap3000c01v2SerialNo OBJECT-TYPE
			SYNTAX SerialNo
			MAX-ACCESS read-only
			STATUS current
			DESCRIPTION
				"Serial number"
		::= { hap3000c01v2Entry 175 }

		-- 1.3.6.1.4.1.10106.3.386801
		psu3300c01v1 OBJECT IDENTIFIER ::= { albalaProducts 386801 }

		-- 1.3.6.1.4.1.10106.3.386801.1
		psu3300c01v1Table  OBJECT-TYPE
			SYNTAX SEQUENCE OF Psu3300c01v1Entry
			MAX-ACCESS not-accessible
			STATUS current
			DESCRIPTION
				"Module  PSU3300C01V1 Table"
			::= { psu3300c01v1 1 }

		-- 1.3.6.1.4.1.10106.3.386801.1.1
		psu3300c01v1Entry  OBJECT-TYPE
			SYNTAX Psu3300c01v1Entry
			MAX-ACCESS not-accessible
			STATUS current
			DESCRIPTION
				"Module PSU3300C01V1 Entry"
			INDEX { psu3300c01v1Index }
			::= { psu3300c01v1Table 1 }

			Psu3300c01v1Entry ::=
			SEQUENCE {
				psu3300c01v1Index
				ModuleIndex,
				psu3300c01v1PowerOff
				BitFail,
				psu3300c01v1PowerOffTrapEnable
				AlarmEnable,
				psu3300c01v1TempWarning
				BitFail,
				psu3300c01v1TempWarningTrapEnable
				AlarmEnable,
				psu3300c01v1TempFail
				BitFail,
				psu3300c01v1TempFailTrapEnable
				AlarmEnable,
				psu3300c01v1ActTemp
				Temperature0c1,
				psu3300c01v1MeanTemp
				Temperature0c1,
				psu3300c01v1MaxTemp
				Temperature0c1,
				psu3300c01v1PonHours
				Uint16,
				psu3300c01v1TotMaxTemp
				Temperature0c1,
				psu3300c01v1TotPonHours
				Uint16,
				psu3300c01v1TotPonTimes
				Uint16,
				psu3300c01v1SerialNo
				SerialNo,
				psu3300c01v1InputVolt
				PsuDcInpV
			 }

		-- 1.3.6.1.4.1.10106.3.101291.1.1.1
		psu3300c01v1Index OBJECT-TYPE
			SYNTAX ModuleIndex
			MAX-ACCESS read-only
			STATUS current
			DESCRIPTION
				"Index of PSU3300C01V1 Table"
		::= { psu3300c01v1Entry 1 }

		-- 1.3.6.1.4.1.10106.3.101291.1.1.3
		psu3300c01v1PowerOff OBJECT-TYPE
			SYNTAX BitFail
			MAX-ACCESS read-only
			STATUS current
			DESCRIPTION
				"Indicates the power supply status"
		::= { psu3300c01v1Entry 3 }

		-- 1.3.6.1.4.1.10106.3.101291.1.1.4
		psu3300c01v1PowerOffTrapEnable OBJECT-TYPE
			SYNTAX AlarmEnable
			MAX-ACCESS read-write
			STATUS current
			DESCRIPTION
				"Indicates the power supply status Trap Enable"
		::= { psu3300c01v1Entry 4 }

		-- 1.3.6.1.4.1.10106.3.101291.1.1.5
		psu3300c01v1TempWarning OBJECT-TYPE
			SYNTAX BitFail
			MAX-ACCESS read-only
			STATUS current
			DESCRIPTION
				"Indicates that actual temperature is over expected range"
		::= { psu3300c01v1Entry 5 }

		-- 1.3.6.1.4.1.10106.3.101291.1.1.6
		psu3300c01v1TempWarningTrapEnable OBJECT-TYPE
			SYNTAX AlarmEnable
			MAX-ACCESS read-write
			STATUS current
			DESCRIPTION
				"Indicates that actual temperature is over expected range Trap Enable"
		::= { psu3300c01v1Entry 6 }

		-- 1.3.6.1.4.1.10106.3.101291.1.1.7
		psu3300c01v1TempFail OBJECT-TYPE
			SYNTAX BitFail
			MAX-ACCESS read-only
			STATUS current
			DESCRIPTION
				"Indicates that actual temperature is over recommended range"
		::= { psu3300c01v1Entry 7 }

		-- 1.3.6.1.4.1.10106.3.101291.1.1.8
		psu3300c01v1TempFailTrapEnable OBJECT-TYPE
			SYNTAX AlarmEnable
			MAX-ACCESS read-write
			STATUS current
			DESCRIPTION
				"Indicates that actual temperature is over recommended range Trap Enable"
		::= { psu3300c01v1Entry 8 }

		-- 1.3.6.1.4.1.10106.3.101291.1.1.9
		psu3300c01v1ActTemp OBJECT-TYPE
			SYNTAX Temperature0c1
			MAX-ACCESS read-only
			STATUS current
			DESCRIPTION
				"Displays internal actual temperature"
		::= { psu3300c01v1Entry 9 }

		-- 1.3.6.1.4.1.10106.3.101291.1.1.11
		psu3300c01v1MeanTemp OBJECT-TYPE
			SYNTAX Temperature0c1
			MAX-ACCESS read-only
			STATUS current
			DESCRIPTION
				"Displays internal mean temperature"
		::= { psu3300c01v1Entry 11 }

		-- 1.3.6.1.4.1.10106.3.101291.1.1.13
		psu3300c01v1MaxTemp OBJECT-TYPE
			SYNTAX Temperature0c1
			MAX-ACCESS read-only
			STATUS current
			DESCRIPTION
				"Displays internal maximun temperature"
		::= { psu3300c01v1Entry 13 }

		-- 1.3.6.1.4.1.10106.3.101291.1.1.15
		psu3300c01v1PonHours OBJECT-TYPE
			SYNTAX Uint16
			MAX-ACCESS read-only
			STATUS current
			DESCRIPTION
				"Displays module power on time"
		::= { psu3300c01v1Entry 15 }

		-- 1.3.6.1.4.1.10106.3.101291.1.1.17
		psu3300c01v1TotMaxTemp OBJECT-TYPE
			SYNTAX Temperature0c1
			MAX-ACCESS read-only
			STATUS current
			DESCRIPTION
				"Displays internal maximun tempertature since first power on"
		::= { psu3300c01v1Entry 17 }

		-- 1.3.6.1.4.1.10106.3.101291.1.1.19
		psu3300c01v1TotPonHours OBJECT-TYPE
			SYNTAX Uint16
			MAX-ACCESS read-only
			STATUS current
			DESCRIPTION
				"Displays module power on time since first power on"
		::= { psu3300c01v1Entry 19 }

		-- 1.3.6.1.4.1.10106.3.101291.1.1.21
		psu3300c01v1TotPonTimes OBJECT-TYPE
			SYNTAX Uint16
			MAX-ACCESS read-only
			STATUS current
			DESCRIPTION
				"Displays module power on events since first power on"
		::= { psu3300c01v1Entry 21 }

		-- 1.3.6.1.4.1.10106.3.101291.1.1.23
		psu3300c01v1SerialNo OBJECT-TYPE
			SYNTAX SerialNo
			MAX-ACCESS read-only
			STATUS current
			DESCRIPTION
				"Serial number"
		::= { psu3300c01v1Entry 23 }

		-- 1.3.6.1.4.1.10106.3.101291.1.1.25
		psu3300c01v1InputVolt OBJECT-TYPE
			SYNTAX PsuDcInpV
			MAX-ACCESS read-only
			STATUS current
			DESCRIPTION
				"Displays the DC input voltaje"
		::= { psu3300c01v1Entry 25 }

		-- 1.3.6.1.4.1.10106.3.388901
		psu3300c02v1 OBJECT IDENTIFIER ::= { albalaProducts 388901 }

		-- 1.3.6.1.4.1.10106.3.388901.1
		psu3300c02v1Table  OBJECT-TYPE
			SYNTAX SEQUENCE OF Psu3300c02v1Entry
			MAX-ACCESS not-accessible
			STATUS current
			DESCRIPTION
				"Module  PSU3300C02V1 Table"
			::= { psu3300c02v1 1 }

		-- 1.3.6.1.4.1.10106.3.388901.1.1
		psu3300c02v1Entry  OBJECT-TYPE
			SYNTAX Psu3300c02v1Entry
			MAX-ACCESS not-accessible
			STATUS current
			DESCRIPTION
				"Module PSU3300C02V1 Entry"
			INDEX { psu3300c02v1Index }
			::= { psu3300c02v1Table 1 }

			Psu3300c02v1Entry ::=
			SEQUENCE {
				psu3300c02v1Index
				ModuleIndex,
				psu3300c02v1PowerOff
				BitFail,
				psu3300c02v1PowerOffTrapEnable
				AlarmEnable,
				psu3300c02v1TempWarning
				BitFail,
				psu3300c02v1TempWarningTrapEnable
				AlarmEnable,
				psu3300c02v1TempFail
				BitFail,
				psu3300c02v1TempFailTrapEnable
				AlarmEnable,
				psu3300c02v1ActTemp
				Temperature0c1,
				psu3300c02v1MeanTemp
				Temperature0c1,
				psu3300c02v1MaxTemp
				Temperature0c1,
				psu3300c02v1PonHours
				Uint16,
				psu3300c02v1TotMaxTemp
				Temperature0c1,
				psu3300c02v1TotPonHours
				Uint16,
				psu3300c02v1TotPonTimes
				Uint16,
				psu3300c02v1SerialNo
				SerialNo
			 }

		-- 1.3.6.1.4.1.10106.3.101291.1.1.1
		psu3300c02v1Index OBJECT-TYPE
			SYNTAX ModuleIndex
			MAX-ACCESS read-only
			STATUS current
			DESCRIPTION
				"Index of PSU3300C02V1 Table"
		::= { psu3300c02v1Entry 1 }

		-- 1.3.6.1.4.1.10106.3.101291.1.1.3
		psu3300c02v1PowerOff OBJECT-TYPE
			SYNTAX BitFail
			MAX-ACCESS read-only
			STATUS current
			DESCRIPTION
				"Indicates the power supply status"
		::= { psu3300c02v1Entry 3 }

		-- 1.3.6.1.4.1.10106.3.101291.1.1.4
		psu3300c02v1PowerOffTrapEnable OBJECT-TYPE
			SYNTAX AlarmEnable
			MAX-ACCESS read-write
			STATUS current
			DESCRIPTION
				"Indicates the power supply status Trap Enable"
		::= { psu3300c02v1Entry 4 }

		-- 1.3.6.1.4.1.10106.3.101291.1.1.5
		psu3300c02v1TempWarning OBJECT-TYPE
			SYNTAX BitFail
			MAX-ACCESS read-only
			STATUS current
			DESCRIPTION
				"Indicates that actual temperature is over expected range"
		::= { psu3300c02v1Entry 5 }

		-- 1.3.6.1.4.1.10106.3.101291.1.1.6
		psu3300c02v1TempWarningTrapEnable OBJECT-TYPE
			SYNTAX AlarmEnable
			MAX-ACCESS read-write
			STATUS current
			DESCRIPTION
				"Indicates that actual temperature is over expected range Trap Enable"
		::= { psu3300c02v1Entry 6 }

		-- 1.3.6.1.4.1.10106.3.101291.1.1.7
		psu3300c02v1TempFail OBJECT-TYPE
			SYNTAX BitFail
			MAX-ACCESS read-only
			STATUS current
			DESCRIPTION
				"Indicates that actual temperature is over recommended range"
		::= { psu3300c02v1Entry 7 }

		-- 1.3.6.1.4.1.10106.3.101291.1.1.8
		psu3300c02v1TempFailTrapEnable OBJECT-TYPE
			SYNTAX AlarmEnable
			MAX-ACCESS read-write
			STATUS current
			DESCRIPTION
				"Indicates that actual temperature is over recommended range Trap Enable"
		::= { psu3300c02v1Entry 8 }

		-- 1.3.6.1.4.1.10106.3.101291.1.1.9
		psu3300c02v1ActTemp OBJECT-TYPE
			SYNTAX Temperature0c1
			MAX-ACCESS read-only
			STATUS current
			DESCRIPTION
				"Displays internal actual temperature"
		::= { psu3300c02v1Entry 9 }

		-- 1.3.6.1.4.1.10106.3.101291.1.1.11
		psu3300c02v1MeanTemp OBJECT-TYPE
			SYNTAX Temperature0c1
			MAX-ACCESS read-only
			STATUS current
			DESCRIPTION
				"Displays internal mean temperature"
		::= { psu3300c02v1Entry 11 }

		-- 1.3.6.1.4.1.10106.3.101291.1.1.13
		psu3300c02v1MaxTemp OBJECT-TYPE
			SYNTAX Temperature0c1
			MAX-ACCESS read-only
			STATUS current
			DESCRIPTION
				"Displays internal maximum temperature"
		::= { psu3300c02v1Entry 13 }

		-- 1.3.6.1.4.1.10106.3.101291.1.1.15
		psu3300c02v1PonHours OBJECT-TYPE
			SYNTAX Uint16
			MAX-ACCESS read-only
			STATUS current
			DESCRIPTION
				"Displays module power on time"
		::= { psu3300c02v1Entry 15 }

		-- 1.3.6.1.4.1.10106.3.101291.1.1.17
		psu3300c02v1TotMaxTemp OBJECT-TYPE
			SYNTAX Temperature0c1
			MAX-ACCESS read-only
			STATUS current
			DESCRIPTION
				"Displays internal maximum tempertature since first power on"
		::= { psu3300c02v1Entry 17 }

		-- 1.3.6.1.4.1.10106.3.101291.1.1.19
		psu3300c02v1TotPonHours OBJECT-TYPE
			SYNTAX Uint16
			MAX-ACCESS read-only
			STATUS current
			DESCRIPTION
				"Displays module power on time since first power on"
		::= { psu3300c02v1Entry 19 }

		-- 1.3.6.1.4.1.10106.3.101291.1.1.21
		psu3300c02v1TotPonTimes OBJECT-TYPE
			SYNTAX Uint16
			MAX-ACCESS read-only
			STATUS current
			DESCRIPTION
				"Displays module power on events since first power on"
		::= { psu3300c02v1Entry 21 }

		-- 1.3.6.1.4.1.10106.3.101291.1.1.23
		psu3300c02v1SerialNo OBJECT-TYPE
			SYNTAX SerialNo
			MAX-ACCESS read-only
			STATUS current
			DESCRIPTION
				"Serial number"
		::= { psu3300c02v1Entry 23 }

		-- 1.3.6.1.4.1.10106.3.389201
		psu3301c01v1 OBJECT IDENTIFIER ::= { albalaProducts 389201 }

		-- 1.3.6.1.4.1.10106.3.389201.1
		psu3301c01v1Table  OBJECT-TYPE
			SYNTAX SEQUENCE OF Psu3301c01v1Entry
			MAX-ACCESS not-accessible
			STATUS current
			DESCRIPTION
				"Module  PSU3301C01V1 Table"
			::= { psu3301c01v1 1 }

		-- 1.3.6.1.4.1.10106.3.389201.1.1
		psu3301c01v1Entry  OBJECT-TYPE
			SYNTAX Psu3301c01v1Entry
			MAX-ACCESS not-accessible
			STATUS current
			DESCRIPTION
				"Module PSU3301C01V1 Entry"
			INDEX { psu3301c01v1Index }
			::= { psu3301c01v1Table 1 }

			Psu3301c01v1Entry ::=
			SEQUENCE {
				psu3301c01v1Index
				ModuleIndex,
				psu3301c01v1PowerOff
				BitFail,
				psu3301c01v1PowerOffTrapEnable
				AlarmEnable,
				psu3301c01v1TempWarning
				BitFail,
				psu3301c01v1TempWarningTrapEnable
				AlarmEnable,
				psu3301c01v1TempFail
				BitFail,
				psu3301c01v1TempFailTrapEnable
				AlarmEnable,
				psu3301c01v1ActTemp
				Temperature0c1,
				psu3301c01v1MeanTemp
				Temperature0c1,
				psu3301c01v1MaxTemp
				Temperature0c1,
				psu3301c01v1PonHours
				Uint16,
				psu3301c01v1TotMaxTemp
				Temperature0c1,
				psu3301c01v1TotPonHours
				Uint16,
				psu3301c01v1TotPonTimes
				Uint16,
				psu3301c01v1SerialNo
				SerialNo,
				psu3301c01v1InputVolt
				PsuDcInpV
			 }

		-- 1.3.6.1.4.1.10106.3.101291.1.1.1
		psu3301c01v1Index OBJECT-TYPE
			SYNTAX ModuleIndex
			MAX-ACCESS read-only
			STATUS current
			DESCRIPTION
				"Index of PSU3301C01V1 Table"
		::= { psu3301c01v1Entry 1 }

		-- 1.3.6.1.4.1.10106.3.101291.1.1.3
		psu3301c01v1PowerOff OBJECT-TYPE
			SYNTAX BitFail
			MAX-ACCESS read-only
			STATUS current
			DESCRIPTION
				"Indicates the power supply status"
		::= { psu3301c01v1Entry 3 }

		-- 1.3.6.1.4.1.10106.3.101291.1.1.4
		psu3301c01v1PowerOffTrapEnable OBJECT-TYPE
			SYNTAX AlarmEnable
			MAX-ACCESS read-write
			STATUS current
			DESCRIPTION
				"Indicates the power supply status Trap Enable"
		::= { psu3301c01v1Entry 4 }

		-- 1.3.6.1.4.1.10106.3.101291.1.1.5
		psu3301c01v1TempWarning OBJECT-TYPE
			SYNTAX BitFail
			MAX-ACCESS read-only
			STATUS current
			DESCRIPTION
				"Indicates that actual temperature is over expected range"
		::= { psu3301c01v1Entry 5 }

		-- 1.3.6.1.4.1.10106.3.101291.1.1.6
		psu3301c01v1TempWarningTrapEnable OBJECT-TYPE
			SYNTAX AlarmEnable
			MAX-ACCESS read-write
			STATUS current
			DESCRIPTION
				"Indicates that actual temperature is over expected range Trap Enable"
		::= { psu3301c01v1Entry 6 }

		-- 1.3.6.1.4.1.10106.3.101291.1.1.7
		psu3301c01v1TempFail OBJECT-TYPE
			SYNTAX BitFail
			MAX-ACCESS read-only
			STATUS current
			DESCRIPTION
				"Indicates that actual temperature is over recommended range"
		::= { psu3301c01v1Entry 7 }

		-- 1.3.6.1.4.1.10106.3.101291.1.1.8
		psu3301c01v1TempFailTrapEnable OBJECT-TYPE
			SYNTAX AlarmEnable
			MAX-ACCESS read-write
			STATUS current
			DESCRIPTION
				"Indicates that actual temperature is over recommended range Trap Enable"
		::= { psu3301c01v1Entry 8 }

		-- 1.3.6.1.4.1.10106.3.101291.1.1.9
		psu3301c01v1ActTemp OBJECT-TYPE
			SYNTAX Temperature0c1
			MAX-ACCESS read-only
			STATUS current
			DESCRIPTION
				"Displays internal actual temperature"
		::= { psu3301c01v1Entry 9 }

		-- 1.3.6.1.4.1.10106.3.101291.1.1.11
		psu3301c01v1MeanTemp OBJECT-TYPE
			SYNTAX Temperature0c1
			MAX-ACCESS read-only
			STATUS current
			DESCRIPTION
				"Displays internal mean temperature"
		::= { psu3301c01v1Entry 11 }

		-- 1.3.6.1.4.1.10106.3.101291.1.1.13
		psu3301c01v1MaxTemp OBJECT-TYPE
			SYNTAX Temperature0c1
			MAX-ACCESS read-only
			STATUS current
			DESCRIPTION
				"Displays internal maximun temperature"
		::= { psu3301c01v1Entry 13 }

		-- 1.3.6.1.4.1.10106.3.101291.1.1.15
		psu3301c01v1PonHours OBJECT-TYPE
			SYNTAX Uint16
			MAX-ACCESS read-only
			STATUS current
			DESCRIPTION
				"Displays module power on time"
		::= { psu3301c01v1Entry 15 }

		-- 1.3.6.1.4.1.10106.3.101291.1.1.17
		psu3301c01v1TotMaxTemp OBJECT-TYPE
			SYNTAX Temperature0c1
			MAX-ACCESS read-only
			STATUS current
			DESCRIPTION
				"Displays internal maximun tempertature since first power on"
		::= { psu3301c01v1Entry 17 }

		-- 1.3.6.1.4.1.10106.3.101291.1.1.19
		psu3301c01v1TotPonHours OBJECT-TYPE
			SYNTAX Uint16
			MAX-ACCESS read-only
			STATUS current
			DESCRIPTION
				"Displays module power on time since first power on"
		::= { psu3301c01v1Entry 19 }

		-- 1.3.6.1.4.1.10106.3.101291.1.1.21
		psu3301c01v1TotPonTimes OBJECT-TYPE
			SYNTAX Uint16
			MAX-ACCESS read-only
			STATUS current
			DESCRIPTION
				"Displays module power on events since first power on"
		::= { psu3301c01v1Entry 21 }

		-- 1.3.6.1.4.1.10106.3.101291.1.1.23
		psu3301c01v1SerialNo OBJECT-TYPE
			SYNTAX SerialNo
			MAX-ACCESS read-only
			STATUS current
			DESCRIPTION
				"Serial number"
		::= { psu3301c01v1Entry 23 }

		-- 1.3.6.1.4.1.10106.3.101291.1.1.25
		psu3301c01v1InputVolt OBJECT-TYPE
			SYNTAX PsuDcInpV
			MAX-ACCESS read-only
			STATUS current
			DESCRIPTION
				"Displays the DC input voltaje"
		::= { psu3301c01v1Entry 25 }

		-- 1.3.6.1.4.1.10106.3.389501
		psu3301c03v1 OBJECT IDENTIFIER ::= { albalaProducts 389501 }

		-- 1.3.6.1.4.1.10106.3.389501.1
		psu3301c03v1Table  OBJECT-TYPE
			SYNTAX SEQUENCE OF Psu3301c03v1Entry
			MAX-ACCESS not-accessible
			STATUS current
			DESCRIPTION
				"Module  PSU3301C03V1 Table"
			::= { psu3301c03v1 1 }

		-- 1.3.6.1.4.1.10106.3.389501.1.1
		psu3301c03v1Entry  OBJECT-TYPE
			SYNTAX Psu3301c03v1Entry
			MAX-ACCESS not-accessible
			STATUS current
			DESCRIPTION
				"Module PSU3301C03V1 Entry"
			INDEX { psu3301c03v1Index }
			::= { psu3301c03v1Table 1 }

			Psu3301c03v1Entry ::=
			SEQUENCE {
				psu3301c03v1Index
				ModuleIndex,
				psu3301c03v1PowerOff
				BitFail,
				psu3301c03v1PowerOffTrapEnable
				AlarmEnable,
				psu3301c03v1TempWarning
				BitFail,
				psu3301c03v1TempWarningTrapEnable
				AlarmEnable,
				psu3301c03v1TempFail
				BitFail,
				psu3301c03v1TempFailTrapEnable
				AlarmEnable,
				psu3301c03v1ActTemp
				Temperature0c1,
				psu3301c03v1MeanTemp
				Temperature0c1,
				psu3301c03v1MaxTemp
				Temperature0c1,
				psu3301c03v1PonHours
				Uint16,
				psu3301c03v1TotMaxTemp
				Temperature0c1,
				psu3301c03v1TotPonHours
				Uint16,
				psu3301c03v1TotPonTimes
				Uint16,
				psu3301c03v1SerialNo
				SerialNo,
				psu3301c03v1InputVolt
				PsuDcInpV
			 }

		-- 1.3.6.1.4.1.10106.3.101291.1.1.1
		psu3301c03v1Index OBJECT-TYPE
			SYNTAX ModuleIndex
			MAX-ACCESS read-only
			STATUS current
			DESCRIPTION
				"Index of PSU3301C03V1 Table"
		::= { psu3301c03v1Entry 1 }

		-- 1.3.6.1.4.1.10106.3.101291.1.1.3
		psu3301c03v1PowerOff OBJECT-TYPE
			SYNTAX BitFail
			MAX-ACCESS read-only
			STATUS current
			DESCRIPTION
				"Indicates the power supply status"
		::= { psu3301c03v1Entry 3 }

		-- 1.3.6.1.4.1.10106.3.101291.1.1.4
		psu3301c03v1PowerOffTrapEnable OBJECT-TYPE
			SYNTAX AlarmEnable
			MAX-ACCESS read-write
			STATUS current
			DESCRIPTION
				"Indicates the power supply status Trap Enable"
		::= { psu3301c03v1Entry 4 }

		-- 1.3.6.1.4.1.10106.3.101291.1.1.5
		psu3301c03v1TempWarning OBJECT-TYPE
			SYNTAX BitFail
			MAX-ACCESS read-only
			STATUS current
			DESCRIPTION
				"Indicates that actual temperature is over expected range"
		::= { psu3301c03v1Entry 5 }

		-- 1.3.6.1.4.1.10106.3.101291.1.1.6
		psu3301c03v1TempWarningTrapEnable OBJECT-TYPE
			SYNTAX AlarmEnable
			MAX-ACCESS read-write
			STATUS current
			DESCRIPTION
				"Indicates that actual temperature is over expected range Trap Enable"
		::= { psu3301c03v1Entry 6 }

		-- 1.3.6.1.4.1.10106.3.101291.1.1.7
		psu3301c03v1TempFail OBJECT-TYPE
			SYNTAX BitFail
			MAX-ACCESS read-only
			STATUS current
			DESCRIPTION
				"Indicates that actual temperature is over recommended range"
		::= { psu3301c03v1Entry 7 }

		-- 1.3.6.1.4.1.10106.3.101291.1.1.8
		psu3301c03v1TempFailTrapEnable OBJECT-TYPE
			SYNTAX AlarmEnable
			MAX-ACCESS read-write
			STATUS current
			DESCRIPTION
				"Indicates that actual temperature is over recommended range Trap Enable"
		::= { psu3301c03v1Entry 8 }

		-- 1.3.6.1.4.1.10106.3.101291.1.1.9
		psu3301c03v1ActTemp OBJECT-TYPE
			SYNTAX Temperature0c1
			MAX-ACCESS read-only
			STATUS current
			DESCRIPTION
				"Displays internal actual temperature"
		::= { psu3301c03v1Entry 9 }

		-- 1.3.6.1.4.1.10106.3.101291.1.1.11
		psu3301c03v1MeanTemp OBJECT-TYPE
			SYNTAX Temperature0c1
			MAX-ACCESS read-only
			STATUS current
			DESCRIPTION
				"Displays internal mean temperature"
		::= { psu3301c03v1Entry 11 }

		-- 1.3.6.1.4.1.10106.3.101291.1.1.13
		psu3301c03v1MaxTemp OBJECT-TYPE
			SYNTAX Temperature0c1
			MAX-ACCESS read-only
			STATUS current
			DESCRIPTION
				"Displays internal maximum temperature"
		::= { psu3301c03v1Entry 13 }

		-- 1.3.6.1.4.1.10106.3.101291.1.1.15
		psu3301c03v1PonHours OBJECT-TYPE
			SYNTAX Uint16
			MAX-ACCESS read-only
			STATUS current
			DESCRIPTION
				"Displays module power on time"
		::= { psu3301c03v1Entry 15 }

		-- 1.3.6.1.4.1.10106.3.101291.1.1.17
		psu3301c03v1TotMaxTemp OBJECT-TYPE
			SYNTAX Temperature0c1
			MAX-ACCESS read-only
			STATUS current
			DESCRIPTION
				"Displays internal maximum tempertature since first power on"
		::= { psu3301c03v1Entry 17 }

		-- 1.3.6.1.4.1.10106.3.101291.1.1.19
		psu3301c03v1TotPonHours OBJECT-TYPE
			SYNTAX Uint16
			MAX-ACCESS read-only
			STATUS current
			DESCRIPTION
				"Displays module power on time since first power on"
		::= { psu3301c03v1Entry 19 }

		-- 1.3.6.1.4.1.10106.3.101291.1.1.21
		psu3301c03v1TotPonTimes OBJECT-TYPE
			SYNTAX Uint16
			MAX-ACCESS read-only
			STATUS current
			DESCRIPTION
				"Displays module power on events since first power on"
		::= { psu3301c03v1Entry 21 }

		-- 1.3.6.1.4.1.10106.3.101291.1.1.23
		psu3301c03v1SerialNo OBJECT-TYPE
			SYNTAX SerialNo
			MAX-ACCESS read-only
			STATUS current
			DESCRIPTION
				"Serial number"
		::= { psu3301c03v1Entry 23 }

		-- 1.3.6.1.4.1.10106.3.101291.1.1.25
		psu3301c03v1InputVolt OBJECT-TYPE
			SYNTAX PsuDcInpV
			MAX-ACCESS read-only
			STATUS current
			DESCRIPTION
				"Displays the DC input voltaje"
		::= { psu3301c03v1Entry 25 }

		-- 1.3.6.1.4.1.10106.3.392001
		avd3001c02v1 OBJECT IDENTIFIER ::= { albalaProducts 392001 }

		-- 1.3.6.1.4.1.10106.3.392001.1
		avd3001c02v1Table  OBJECT-TYPE
			SYNTAX SEQUENCE OF Avd3001c02v1Entry
			MAX-ACCESS not-accessible
			STATUS current
			DESCRIPTION
				"Module  AVD3001C02V1 Table"
			::= { avd3001c02v1 1 }

		-- 1.3.6.1.4.1.10106.3.392001.1.1
		avd3001c02v1Entry  OBJECT-TYPE
			SYNTAX Avd3001c02v1Entry
			MAX-ACCESS not-accessible
			STATUS current
			DESCRIPTION
				"Module AVD3001C02V1 Entry"
			INDEX { avd3001c02v1Index }
			::= { avd3001c02v1Table 1 }

			Avd3001c02v1Entry ::=
			SEQUENCE {
				avd3001c02v1Index
				ModuleIndex,
				avd3001c02v1ClampEnable
				Bit0No1Yes,
				avd3001c02v1ClampMode
				Bit0No1Yes,
				avd3001c02v1NoSigA
				BitFail,
				avd3001c02v1NoSigATrapEnable
				AlarmEnable,
				avd3001c02v1UnlockA
				BitFail,
				avd3001c02v1UnlockATrapEnable
				AlarmEnable,
				avd3001c02v1SyncFormat
				SdiHd3gFmt3,
				avd3001c02v1SyncFormatTrapEnable
				AlarmEnable,
				avd3001c02v1SerialNo
				SerialNo
			 }

		-- 1.3.6.1.4.1.10106.3.101291.1.1.1
		avd3001c02v1Index OBJECT-TYPE
			SYNTAX ModuleIndex
			MAX-ACCESS read-only
			STATUS current
			DESCRIPTION
				"Index of AVD3001C02V1 Table"
		::= { avd3001c02v1Entry 1 }

		-- 1.3.6.1.4.1.10106.3.101291.1.1.3
		avd3001c02v1ClampEnable OBJECT-TYPE
			SYNTAX Bit0No1Yes
			MAX-ACCESS read-write
			STATUS current
			DESCRIPTION
				"Allows enabling clamping"
		::= { avd3001c02v1Entry 3 }

		-- 1.3.6.1.4.1.10106.3.101291.1.1.5
		avd3001c02v1ClampMode OBJECT-TYPE
			SYNTAX Bit0No1Yes
			MAX-ACCESS read-write
			STATUS current
			DESCRIPTION
				"Allows selecting soft clamping"
		::= { avd3001c02v1Entry 5 }

		-- 1.3.6.1.4.1.10106.3.101291.1.1.7
		avd3001c02v1NoSigA OBJECT-TYPE
			SYNTAX BitFail
			MAX-ACCESS read-only
			STATUS current
			DESCRIPTION
				"Input signal status"
		::= { avd3001c02v1Entry 7 }

		-- 1.3.6.1.4.1.10106.3.101291.1.1.8
		avd3001c02v1NoSigATrapEnable OBJECT-TYPE
			SYNTAX AlarmEnable
			MAX-ACCESS read-write
			STATUS current
			DESCRIPTION
				"Input signal status Trap Enable"
		::= { avd3001c02v1Entry 8 }

		-- 1.3.6.1.4.1.10106.3.101291.1.1.9
		avd3001c02v1UnlockA OBJECT-TYPE
			SYNTAX BitFail
			MAX-ACCESS read-only
			STATUS current
			DESCRIPTION
				"Indicates signal unlock fail"
		::= { avd3001c02v1Entry 9 }

		-- 1.3.6.1.4.1.10106.3.101291.1.1.10
		avd3001c02v1UnlockATrapEnable OBJECT-TYPE
			SYNTAX AlarmEnable
			MAX-ACCESS read-write
			STATUS current
			DESCRIPTION
				"Indicates signal unlock fail Trap Enable"
		::= { avd3001c02v1Entry 10 }

		-- 1.3.6.1.4.1.10106.3.101291.1.1.11
		avd3001c02v1SyncFormat OBJECT-TYPE
			SYNTAX SdiHd3gFmt3
			MAX-ACCESS read-only
			STATUS current
			DESCRIPTION
				"Displays signal's  input format"
		::= { avd3001c02v1Entry 11 }

		-- 1.3.6.1.4.1.10106.3.101291.1.1.12
		avd3001c02v1SyncFormatTrapEnable OBJECT-TYPE
			SYNTAX AlarmEnable
			MAX-ACCESS read-write
			STATUS current
			DESCRIPTION
				"Displays signal's  input format Trap Enable"
		::= { avd3001c02v1Entry 12 }

		-- 1.3.6.1.4.1.10106.3.101291.1.1.13
		avd3001c02v1SerialNo OBJECT-TYPE
			SYNTAX SerialNo
			MAX-ACCESS read-only
			STATUS current
			DESCRIPTION
				"Serial number"
		::= { avd3001c02v1Entry 13 }

		-- 1.3.6.1.4.1.10106.3.393601
		avd3001c01v1 OBJECT IDENTIFIER ::= { albalaProducts 393601 }

		-- 1.3.6.1.4.1.10106.3.393601.1
		avd3001c01v1Table  OBJECT-TYPE
			SYNTAX SEQUENCE OF Avd3001c01v1Entry
			MAX-ACCESS not-accessible
			STATUS current
			DESCRIPTION
				"Module  AVD3001C01V1 Table"
			::= { avd3001c01v1 1 }

		-- 1.3.6.1.4.1.10106.3.393601.1.1
		avd3001c01v1Entry  OBJECT-TYPE
			SYNTAX Avd3001c01v1Entry
			MAX-ACCESS not-accessible
			STATUS current
			DESCRIPTION
				"Module AVD3001C01V1 Entry"
			INDEX { avd3001c01v1Index }
			::= { avd3001c01v1Table 1 }

			Avd3001c01v1Entry ::=
			SEQUENCE {
				avd3001c01v1Index
				ModuleIndex,
				avd3001c01v1ClampEnable
				Bit0No1Yes,
				avd3001c01v1ClampMode
				Bit0No1Yes,
				avd3001c01v1NoSigA
				BitFail,
				avd3001c01v1NoSigATrapEnable
				AlarmEnable,
				avd3001c01v1UnlockA
				BitFail,
				avd3001c01v1UnlockATrapEnable
				AlarmEnable,
				avd3001c01v1SyncFormat
				SdiHd3gFmt3,
				avd3001c01v1SyncFormatTrapEnable
				AlarmEnable,
				avd3001c01v1SerialNo
				SerialNo
			 }

		-- 1.3.6.1.4.1.10106.3.101291.1.1.1
		avd3001c01v1Index OBJECT-TYPE
			SYNTAX ModuleIndex
			MAX-ACCESS read-only
			STATUS current
			DESCRIPTION
				"Index of AVD3001C01V1 Table"
		::= { avd3001c01v1Entry 1 }

		-- 1.3.6.1.4.1.10106.3.101291.1.1.3
		avd3001c01v1ClampEnable OBJECT-TYPE
			SYNTAX Bit0No1Yes
			MAX-ACCESS read-write
			STATUS current
			DESCRIPTION
				"Allows enabling clamping"
		::= { avd3001c01v1Entry 3 }

		-- 1.3.6.1.4.1.10106.3.101291.1.1.5
		avd3001c01v1ClampMode OBJECT-TYPE
			SYNTAX Bit0No1Yes
			MAX-ACCESS read-write
			STATUS current
			DESCRIPTION
				"Allows selecting soft clamping"
		::= { avd3001c01v1Entry 5 }

		-- 1.3.6.1.4.1.10106.3.101291.1.1.7
		avd3001c01v1NoSigA OBJECT-TYPE
			SYNTAX BitFail
			MAX-ACCESS read-only
			STATUS current
			DESCRIPTION
				"Input signal status"
		::= { avd3001c01v1Entry 7 }

		-- 1.3.6.1.4.1.10106.3.101291.1.1.8
		avd3001c01v1NoSigATrapEnable OBJECT-TYPE
			SYNTAX AlarmEnable
			MAX-ACCESS read-write
			STATUS current
			DESCRIPTION
				"Input signal status Trap Enable"
		::= { avd3001c01v1Entry 8 }

		-- 1.3.6.1.4.1.10106.3.101291.1.1.9
		avd3001c01v1UnlockA OBJECT-TYPE
			SYNTAX BitFail
			MAX-ACCESS read-only
			STATUS current
			DESCRIPTION
				"Indicates signal unlock fail"
		::= { avd3001c01v1Entry 9 }

		-- 1.3.6.1.4.1.10106.3.101291.1.1.10
		avd3001c01v1UnlockATrapEnable OBJECT-TYPE
			SYNTAX AlarmEnable
			MAX-ACCESS read-write
			STATUS current
			DESCRIPTION
				"Indicates signal unlock fail Trap Enable"
		::= { avd3001c01v1Entry 10 }

		-- 1.3.6.1.4.1.10106.3.101291.1.1.11
		avd3001c01v1SyncFormat OBJECT-TYPE
			SYNTAX SdiHd3gFmt3
			MAX-ACCESS read-only
			STATUS current
			DESCRIPTION
				"Displays signal's  input format"
		::= { avd3001c01v1Entry 11 }

		-- 1.3.6.1.4.1.10106.3.101291.1.1.12
		avd3001c01v1SyncFormatTrapEnable OBJECT-TYPE
			SYNTAX AlarmEnable
			MAX-ACCESS read-write
			STATUS current
			DESCRIPTION
				"Displays signal's  input format Trap Enable"
		::= { avd3001c01v1Entry 12 }

		-- 1.3.6.1.4.1.10106.3.101291.1.1.13
		avd3001c01v1SerialNo OBJECT-TYPE
			SYNTAX SerialNo
			MAX-ACCESS read-only
			STATUS current
			DESCRIPTION
				"Serial number"
		::= { avd3001c01v1Entry 13 }

		-- 1.3.6.1.4.1.10106.3.393701
		avd3001c03v1 OBJECT IDENTIFIER ::= { albalaProducts 393701 }

		-- 1.3.6.1.4.1.10106.3.393701.1
		avd3001c03v1Table  OBJECT-TYPE
			SYNTAX SEQUENCE OF Avd3001c03v1Entry
			MAX-ACCESS not-accessible
			STATUS current
			DESCRIPTION
				"Module  AVD3001C03V1 Table"
			::= { avd3001c03v1 1 }

		-- 1.3.6.1.4.1.10106.3.393701.1.1
		avd3001c03v1Entry  OBJECT-TYPE
			SYNTAX Avd3001c03v1Entry
			MAX-ACCESS not-accessible
			STATUS current
			DESCRIPTION
				"Module AVD3001C03V1 Entry"
			INDEX { avd3001c03v1Index }
			::= { avd3001c03v1Table 1 }

			Avd3001c03v1Entry ::=
			SEQUENCE {
				avd3001c03v1Index
				ModuleIndex,
				avd3001c03v1NoSigA
				BitFail,
				avd3001c03v1NoSigATrapEnable
				AlarmEnable,
				avd3001c03v1UnlockA
				BitFail,
				avd3001c03v1UnlockATrapEnable
				AlarmEnable,
				avd3001c03v1SyncFormat
				SdiHd3gFmt3,
				avd3001c03v1SyncFormatTrapEnable
				AlarmEnable,
				avd3001c03v1SerialNo
				SerialNo
			 }

		-- 1.3.6.1.4.1.10106.3.101291.1.1.1
		avd3001c03v1Index OBJECT-TYPE
			SYNTAX ModuleIndex
			MAX-ACCESS read-only
			STATUS current
			DESCRIPTION
				"Index of AVD3001C03V1 Table"
		::= { avd3001c03v1Entry 1 }

		-- 1.3.6.1.4.1.10106.3.101291.1.1.3
		avd3001c03v1NoSigA OBJECT-TYPE
			SYNTAX BitFail
			MAX-ACCESS read-only
			STATUS current
			DESCRIPTION
				"Input signal status"
		::= { avd3001c03v1Entry 3 }

		-- 1.3.6.1.4.1.10106.3.101291.1.1.4
		avd3001c03v1NoSigATrapEnable OBJECT-TYPE
			SYNTAX AlarmEnable
			MAX-ACCESS read-write
			STATUS current
			DESCRIPTION
				"Input signal status Trap Enable"
		::= { avd3001c03v1Entry 4 }

		-- 1.3.6.1.4.1.10106.3.101291.1.1.5
		avd3001c03v1UnlockA OBJECT-TYPE
			SYNTAX BitFail
			MAX-ACCESS read-only
			STATUS current
			DESCRIPTION
				"Indicates signal unlock fail"
		::= { avd3001c03v1Entry 5 }

		-- 1.3.6.1.4.1.10106.3.101291.1.1.6
		avd3001c03v1UnlockATrapEnable OBJECT-TYPE
			SYNTAX AlarmEnable
			MAX-ACCESS read-write
			STATUS current
			DESCRIPTION
				"Indicates signal unlock fail Trap Enable"
		::= { avd3001c03v1Entry 6 }

		-- 1.3.6.1.4.1.10106.3.101291.1.1.7
		avd3001c03v1SyncFormat OBJECT-TYPE
			SYNTAX SdiHd3gFmt3
			MAX-ACCESS read-only
			STATUS current
			DESCRIPTION
				"Displays signal's  input format"
		::= { avd3001c03v1Entry 7 }

		-- 1.3.6.1.4.1.10106.3.101291.1.1.8
		avd3001c03v1SyncFormatTrapEnable OBJECT-TYPE
			SYNTAX AlarmEnable
			MAX-ACCESS read-write
			STATUS current
			DESCRIPTION
				"Displays signal's  input format Trap Enable"
		::= { avd3001c03v1Entry 8 }

		-- 1.3.6.1.4.1.10106.3.101291.1.1.9
		avd3001c03v1SerialNo OBJECT-TYPE
			SYNTAX SerialNo
			MAX-ACCESS read-only
			STATUS current
			DESCRIPTION
				"Serial number"
		::= { avd3001c03v1Entry 9 }

		-- 1.3.6.1.4.1.10106.3.399601
		vgp3000c01v1 OBJECT IDENTIFIER ::= { albalaProducts 399601 }

		-- 1.3.6.1.4.1.10106.3.399601.1
		vgp3000c01v1Table  OBJECT-TYPE
			SYNTAX SEQUENCE OF Vgp3000c01v1Entry
			MAX-ACCESS not-accessible
			STATUS current
			DESCRIPTION
				"Module  VGP3000C01V1 Table"
			::= { vgp3000c01v1 1 }

		-- 1.3.6.1.4.1.10106.3.399601.1.1
		vgp3000c01v1Entry  OBJECT-TYPE
			SYNTAX Vgp3000c01v1Entry
			MAX-ACCESS not-accessible
			STATUS current
			DESCRIPTION
				"Module VGP3000C01V1 Entry"
			INDEX { vgp3000c01v1Index }
			::= { vgp3000c01v1Table 1 }

			Vgp3000c01v1Entry ::=
			SEQUENCE {
				vgp3000c01v1Index
				ModuleIndex,
				vgp3000c01v1GpioStatMode
				Bit0No1Yes,
				vgp3000c01v1Gpo1SGpi1Ena
				Bit0No1Yes,
				vgp3000c01v1Gpo1SGpi2Ena
				Bit0No1Yes,
				vgp3000c01v1Gpo1SGpi3Ena
				Bit0No1Yes,
				vgp3000c01v1Gpo1SGpi4Ena
				Bit0No1Yes,
				vgp3000c01v1Gpo1SGpi5Ena
				Bit0No1Yes,
				vgp3000c01v1Gpo1SGpi6Ena
				Bit0No1Yes,
				vgp3000c01v1Gpo1SGpi7Ena
				Bit0No1Yes,
				vgp3000c01v1Gpo1SGpi8Ena
				Bit0No1Yes,
				vgp3000c01v1Gpo1SGpi1Mode
				GpiMode,
				vgp3000c01v1Gpo1SGpi2Mode
				GpiMode,
				vgp3000c01v1Gpo1SGpi3Mode
				GpiMode,
				vgp3000c01v1Gpo1SGpi4Mode
				GpiMode,
				vgp3000c01v1Gpo1SGpi5Mode
				GpiMode,
				vgp3000c01v1Gpo1SGpi6Mode
				GpiMode,
				vgp3000c01v1Gpo1SGpi7Mode
				GpiMode,
				vgp3000c01v1Gpo1SGpi8Mode
				GpiMode,
				vgp3000c01v1Gpo1SDelay
				TimeX10Ms,
				vgp3000c01v1Gpo1SF
				Bit0And1Or,
				vgp3000c01v1Gpo1RGpi1Ena
				Bit0No1Yes,
				vgp3000c01v1Gpo1RGpi2Ena
				Bit0No1Yes,
				vgp3000c01v1Gpo1RGpi3Ena
				Bit0No1Yes,
				vgp3000c01v1Gpo1RGpi4Ena
				Bit0No1Yes,
				vgp3000c01v1Gpo1RGpi5Ena
				Bit0No1Yes,
				vgp3000c01v1Gpo1RGpi6Ena
				Bit0No1Yes,
				vgp3000c01v1Gpo1RGpi7Ena
				Bit0No1Yes,
				vgp3000c01v1Gpo1RGpi8Ena
				Bit0No1Yes,
				vgp3000c01v1Gpo1RGpi1Mode
				GpiMode,
				vgp3000c01v1Gpo1RGpi2Mode
				GpiMode,
				vgp3000c01v1Gpo1RGpi3Mode
				GpiMode,
				vgp3000c01v1Gpo1RGpi4Mode
				GpiMode,
				vgp3000c01v1Gpo1RGpi5Mode
				GpiMode,
				vgp3000c01v1Gpo1RGpi6Mode
				GpiMode,
				vgp3000c01v1Gpo1RGpi7Mode
				GpiMode,
				vgp3000c01v1Gpo1RGpi8Mode
				GpiMode,
				vgp3000c01v1Gpo1RDelay
				TimeX10Ms,
				vgp3000c01v1Gpo1RF
				Bit0And1Or,
				vgp3000c01v1Gpo2SGpi1Ena
				Bit0No1Yes,
				vgp3000c01v1Gpo2SGpi2Ena
				Bit0No1Yes,
				vgp3000c01v1Gpo2SGpi3Ena
				Bit0No1Yes,
				vgp3000c01v1Gpo2SGpi4Ena
				Bit0No1Yes,
				vgp3000c01v1Gpo2SGpi5Ena
				Bit0No1Yes,
				vgp3000c01v1Gpo2SGpi6Ena
				Bit0No1Yes,
				vgp3000c01v1Gpo2SGpi7Ena
				Bit0No1Yes,
				vgp3000c01v1Gpo2SGpi8Ena
				Bit0No1Yes,
				vgp3000c01v1Gpo2SGpi1Mode
				GpiMode,
				vgp3000c01v1Gpo2SGpi2Mode
				GpiMode,
				vgp3000c01v1Gpo2SGpi3Mode
				GpiMode,
				vgp3000c01v1Gpo2SGpi4Mode
				GpiMode,
				vgp3000c01v1Gpo2SGpi5Mode
				GpiMode,
				vgp3000c01v1Gpo2SGpi6Mode
				GpiMode,
				vgp3000c01v1Gpo2SGpi7Mode
				GpiMode,
				vgp3000c01v1Gpo2SGpi8Mode
				GpiMode,
				vgp3000c01v1Gpo2SDelay
				TimeX10Ms,
				vgp3000c01v1Gpo2SF
				Bit0And1Or,
				vgp3000c01v1Gpo2RGpi1Ena
				Bit0No1Yes,
				vgp3000c01v1Gpo2RGpi2Ena
				Bit0No1Yes,
				vgp3000c01v1Gpo2RGpi3Ena
				Bit0No1Yes,
				vgp3000c01v1Gpo2RGpi4Ena
				Bit0No1Yes,
				vgp3000c01v1Gpo2RGpi5Ena
				Bit0No1Yes,
				vgp3000c01v1Gpo2RGpi6Ena
				Bit0No1Yes,
				vgp3000c01v1Gpo2RGpi7Ena
				Bit0No1Yes,
				vgp3000c01v1Gpo2RGpi8Ena
				Bit0No1Yes,
				vgp3000c01v1Gpo2RGpi1Mode
				GpiMode,
				vgp3000c01v1Gpo2RGpi2Mode
				GpiMode,
				vgp3000c01v1Gpo2RGpi3Mode
				GpiMode,
				vgp3000c01v1Gpo2RGpi4Mode
				GpiMode,
				vgp3000c01v1Gpo2RGpi5Mode
				GpiMode,
				vgp3000c01v1Gpo2RGpi6Mode
				GpiMode,
				vgp3000c01v1Gpo2RGpi7Mode
				GpiMode,
				vgp3000c01v1Gpo2RGpi8Mode
				GpiMode,
				vgp3000c01v1Gpo2RDelay
				TimeX10Ms,
				vgp3000c01v1Gpo2RF
				Bit0And1Or,
				vgp3000c01v1Gpo3SGpi1Ena
				Bit0No1Yes,
				vgp3000c01v1Gpo3SGpi2Ena
				Bit0No1Yes,
				vgp3000c01v1Gpo3SGpi3Ena
				Bit0No1Yes,
				vgp3000c01v1Gpo3SGpi4Ena
				Bit0No1Yes,
				vgp3000c01v1Gpo3SGpi5Ena
				Bit0No1Yes,
				vgp3000c01v1Gpo3SGpi6Ena
				Bit0No1Yes,
				vgp3000c01v1Gpo3SGpi7Ena
				Bit0No1Yes,
				vgp3000c01v1Gpo3SGpi8Ena
				Bit0No1Yes,
				vgp3000c01v1Gpo3SGpi1Mode
				GpiMode,
				vgp3000c01v1Gpo3SGpi2Mode
				GpiMode,
				vgp3000c01v1Gpo3SGpi3Mode
				GpiMode,
				vgp3000c01v1Gpo3SGpi4Mode
				GpiMode,
				vgp3000c01v1Gpo3SGpi5Mode
				GpiMode,
				vgp3000c01v1Gpo3SGpi6Mode
				GpiMode,
				vgp3000c01v1Gpo3SGpi7Mode
				GpiMode,
				vgp3000c01v1Gpo3SGpi8Mode
				GpiMode,
				vgp3000c01v1Gpo3SDelay
				TimeX10Ms,
				vgp3000c01v1Gpo3SF
				Bit0And1Or,
				vgp3000c01v1Gpo3RGpi1Ena
				Bit0No1Yes,
				vgp3000c01v1Gpo3RGpi2Ena
				Bit0No1Yes,
				vgp3000c01v1Gpo3RGpi3Ena
				Bit0No1Yes,
				vgp3000c01v1Gpo3RGpi4Ena
				Bit0No1Yes,
				vgp3000c01v1Gpo3RGpi5Ena
				Bit0No1Yes,
				vgp3000c01v1Gpo3RGpi6Ena
				Bit0No1Yes,
				vgp3000c01v1Gpo3RGpi7Ena
				Bit0No1Yes,
				vgp3000c01v1Gpo3RGpi8Ena
				Bit0No1Yes,
				vgp3000c01v1Gpo3RGpi1Mode
				GpiMode,
				vgp3000c01v1Gpo3RGpi2Mode
				GpiMode,
				vgp3000c01v1Gpo3RGpi3Mode
				GpiMode,
				vgp3000c01v1Gpo3RGpi4Mode
				GpiMode,
				vgp3000c01v1Gpo3RGpi5Mode
				GpiMode,
				vgp3000c01v1Gpo3RGpi6Mode
				GpiMode,
				vgp3000c01v1Gpo3RGpi7Mode
				GpiMode,
				vgp3000c01v1Gpo3RGpi8Mode
				GpiMode,
				vgp3000c01v1Gpo3RDelay
				TimeX10Ms,
				vgp3000c01v1Gpo3RF
				Bit0And1Or,
				vgp3000c01v1Gpo4SGpi1Ena
				Bit0No1Yes,
				vgp3000c01v1Gpo4SGpi2Ena
				Bit0No1Yes,
				vgp3000c01v1Gpo4SGpi3Ena
				Bit0No1Yes,
				vgp3000c01v1Gpo4SGpi4Ena
				Bit0No1Yes,
				vgp3000c01v1Gpo4SGpi5Ena
				Bit0No1Yes,
				vgp3000c01v1Gpo4SGpi6Ena
				Bit0No1Yes,
				vgp3000c01v1Gpo4SGpi7Ena
				Bit0No1Yes,
				vgp3000c01v1Gpo4SGpi8Ena
				Bit0No1Yes,
				vgp3000c01v1Gpo4SGpi1Mode
				GpiMode,
				vgp3000c01v1Gpo4SGpi2Mode
				GpiMode,
				vgp3000c01v1Gpo4SGpi3Mode
				GpiMode,
				vgp3000c01v1Gpo4SGpi4Mode
				GpiMode,
				vgp3000c01v1Gpo4SGpi5Mode
				GpiMode,
				vgp3000c01v1Gpo4SGpi6Mode
				GpiMode,
				vgp3000c01v1Gpo4SGpi7Mode
				GpiMode,
				vgp3000c01v1Gpo4SGpi8Mode
				GpiMode,
				vgp3000c01v1Gpo4SDelay
				TimeX10Ms,
				vgp3000c01v1Gpo4SF
				Bit0And1Or,
				vgp3000c01v1Gpo4RGpi1Ena
				Bit0No1Yes,
				vgp3000c01v1Gpo4RGpi2Ena
				Bit0No1Yes,
				vgp3000c01v1Gpo4RGpi3Ena
				Bit0No1Yes,
				vgp3000c01v1Gpo4RGpi4Ena
				Bit0No1Yes,
				vgp3000c01v1Gpo4RGpi5Ena
				Bit0No1Yes,
				vgp3000c01v1Gpo4RGpi6Ena
				Bit0No1Yes,
				vgp3000c01v1Gpo4RGpi7Ena
				Bit0No1Yes,
				vgp3000c01v1Gpo4RGpi8Ena
				Bit0No1Yes,
				vgp3000c01v1Gpo4RGpi1Mode
				GpiMode,
				vgp3000c01v1Gpo4RGpi2Mode
				GpiMode,
				vgp3000c01v1Gpo4RGpi3Mode
				GpiMode,
				vgp3000c01v1Gpo4RGpi4Mode
				GpiMode,
				vgp3000c01v1Gpo4RGpi5Mode
				GpiMode,
				vgp3000c01v1Gpo4RGpi6Mode
				GpiMode,
				vgp3000c01v1Gpo4RGpi7Mode
				GpiMode,
				vgp3000c01v1Gpo4RGpi8Mode
				GpiMode,
				vgp3000c01v1Gpo4RDelay
				TimeX10Ms,
				vgp3000c01v1Gpo4RF
				Bit0And1Or,
				vgp3000c01v1Gpo5SGpi1Ena
				Bit0No1Yes,
				vgp3000c01v1Gpo5SGpi2Ena
				Bit0No1Yes,
				vgp3000c01v1Gpo5SGpi3Ena
				Bit0No1Yes,
				vgp3000c01v1Gpo5SGpi4Ena
				Bit0No1Yes,
				vgp3000c01v1Gpo5SGpi5Ena
				Bit0No1Yes,
				vgp3000c01v1Gpo5SGpi6Ena
				Bit0No1Yes,
				vgp3000c01v1Gpo5SGpi7Ena
				Bit0No1Yes,
				vgp3000c01v1Gpo5SGpi8Ena
				Bit0No1Yes,
				vgp3000c01v1Gpo5SGpi1Mode
				GpiMode,
				vgp3000c01v1Gpo5SGpi2Mode
				GpiMode,
				vgp3000c01v1Gpo5SGpi3Mode
				GpiMode,
				vgp3000c01v1Gpo5SGpi4Mode
				GpiMode,
				vgp3000c01v1Gpo5SGpi5Mode
				GpiMode,
				vgp3000c01v1Gpo5SGpi6Mode
				GpiMode,
				vgp3000c01v1Gpo5SGpi7Mode
				GpiMode,
				vgp3000c01v1Gpo5SGpi8Mode
				GpiMode,
				vgp3000c01v1Gpo5SDelay
				TimeX10Ms,
				vgp3000c01v1Gpo5SF
				Bit0And1Or,
				vgp3000c01v1Gpo5RGpi1Ena
				Bit0No1Yes,
				vgp3000c01v1Gpo5RGpi2Ena
				Bit0No1Yes,
				vgp3000c01v1Gpo5RGpi3Ena
				Bit0No1Yes,
				vgp3000c01v1Gpo5RGpi4Ena
				Bit0No1Yes,
				vgp3000c01v1Gpo5RGpi5Ena
				Bit0No1Yes,
				vgp3000c01v1Gpo5RGpi6Ena
				Bit0No1Yes,
				vgp3000c01v1Gpo5RGpi7Ena
				Bit0No1Yes,
				vgp3000c01v1Gpo5RGpi8Ena
				Bit0No1Yes,
				vgp3000c01v1Gpo5RGpi1Mode
				GpiMode,
				vgp3000c01v1Gpo5RGpi2Mode
				GpiMode,
				vgp3000c01v1Gpo5RGpi3Mode
				GpiMode,
				vgp3000c01v1Gpo5RGpi4Mode
				GpiMode,
				vgp3000c01v1Gpo5RGpi5Mode
				GpiMode,
				vgp3000c01v1Gpo5RGpi6Mode
				GpiMode,
				vgp3000c01v1Gpo5RGpi7Mode
				GpiMode,
				vgp3000c01v1Gpo5RGpi8Mode
				GpiMode,
				vgp3000c01v1Gpo5RDelay
				TimeX10Ms,
				vgp3000c01v1Gpo5RF
				Bit0And1Or,
				vgp3000c01v1Gpo6SGpi1Ena
				Bit0No1Yes,
				vgp3000c01v1Gpo6SGpi2Ena
				Bit0No1Yes,
				vgp3000c01v1Gpo6SGpi3Ena
				Bit0No1Yes,
				vgp3000c01v1Gpo6SGpi4Ena
				Bit0No1Yes,
				vgp3000c01v1Gpo6SGpi5Ena
				Bit0No1Yes,
				vgp3000c01v1Gpo6SGpi6Ena
				Bit0No1Yes,
				vgp3000c01v1Gpo6SGpi7Ena
				Bit0No1Yes,
				vgp3000c01v1Gpo6SGpi8Ena
				Bit0No1Yes,
				vgp3000c01v1Gpo6SGpi1Mode
				GpiMode,
				vgp3000c01v1Gpo6SGpi2Mode
				GpiMode,
				vgp3000c01v1Gpo6SGpi3Mode
				GpiMode,
				vgp3000c01v1Gpo6SGpi4Mode
				GpiMode,
				vgp3000c01v1Gpo6SGpi5Mode
				GpiMode,
				vgp3000c01v1Gpo6SGpi6Mode
				GpiMode,
				vgp3000c01v1Gpo6SGpi7Mode
				GpiMode,
				vgp3000c01v1Gpo6SGpi8Mode
				GpiMode,
				vgp3000c01v1Gpo6SDelay
				TimeX10Ms,
				vgp3000c01v1Gpo6SF
				Bit0And1Or,
				vgp3000c01v1Gpo6RGpi1Ena
				Bit0No1Yes,
				vgp3000c01v1Gpo6RGpi2Ena
				Bit0No1Yes,
				vgp3000c01v1Gpo6RGpi3Ena
				Bit0No1Yes,
				vgp3000c01v1Gpo6RGpi4Ena
				Bit0No1Yes,
				vgp3000c01v1Gpo6RGpi5Ena
				Bit0No1Yes,
				vgp3000c01v1Gpo6RGpi6Ena
				Bit0No1Yes,
				vgp3000c01v1Gpo6RGpi7Ena
				Bit0No1Yes,
				vgp3000c01v1Gpo6RGpi8Ena
				Bit0No1Yes,
				vgp3000c01v1Gpo6RGpi1Mode
				GpiMode,
				vgp3000c01v1Gpo6RGpi2Mode
				GpiMode,
				vgp3000c01v1Gpo6RGpi3Mode
				GpiMode,
				vgp3000c01v1Gpo6RGpi4Mode
				GpiMode,
				vgp3000c01v1Gpo6RGpi5Mode
				GpiMode,
				vgp3000c01v1Gpo6RGpi6Mode
				GpiMode,
				vgp3000c01v1Gpo6RGpi7Mode
				GpiMode,
				vgp3000c01v1Gpo6RGpi8Mode
				GpiMode,
				vgp3000c01v1Gpo6RDelay
				TimeX10Ms,
				vgp3000c01v1Gpo6RF
				Bit0And1Or,
				vgp3000c01v1Gpo7SGpi1Ena
				Bit0No1Yes,
				vgp3000c01v1Gpo7SGpi2Ena
				Bit0No1Yes,
				vgp3000c01v1Gpo7SGpi3Ena
				Bit0No1Yes,
				vgp3000c01v1Gpo7SGpi4Ena
				Bit0No1Yes,
				vgp3000c01v1Gpo7SGpi5Ena
				Bit0No1Yes,
				vgp3000c01v1Gpo7SGpi6Ena
				Bit0No1Yes,
				vgp3000c01v1Gpo7SGpi7Ena
				Bit0No1Yes,
				vgp3000c01v1Gpo7SGpi8Ena
				Bit0No1Yes,
				vgp3000c01v1Gpo7SGpi1Mode
				GpiMode,
				vgp3000c01v1Gpo7SGpi2Mode
				GpiMode,
				vgp3000c01v1Gpo7SGpi3Mode
				GpiMode,
				vgp3000c01v1Gpo7SGpi4Mode
				GpiMode,
				vgp3000c01v1Gpo7SGpi5Mode
				GpiMode,
				vgp3000c01v1Gpo7SGpi6Mode
				GpiMode,
				vgp3000c01v1Gpo7SGpi7Mode
				GpiMode,
				vgp3000c01v1Gpo7SGpi8Mode
				GpiMode,
				vgp3000c01v1Gpo7SDelay
				TimeX10Ms,
				vgp3000c01v1Gpo7SF
				Bit0And1Or,
				vgp3000c01v1Gpo7RGpi1Ena
				Bit0No1Yes,
				vgp3000c01v1Gpo7RGpi2Ena
				Bit0No1Yes,
				vgp3000c01v1Gpo7RGpi3Ena
				Bit0No1Yes,
				vgp3000c01v1Gpo7RGpi4Ena
				Bit0No1Yes,
				vgp3000c01v1Gpo7RGpi5Ena
				Bit0No1Yes,
				vgp3000c01v1Gpo7RGpi6Ena
				Bit0No1Yes,
				vgp3000c01v1Gpo7RGpi7Ena
				Bit0No1Yes,
				vgp3000c01v1Gpo7RGpi8Ena
				Bit0No1Yes,
				vgp3000c01v1Gpo7RGpi1Mode
				GpiMode,
				vgp3000c01v1Gpo7RGpi2Mode
				GpiMode,
				vgp3000c01v1Gpo7RGpi3Mode
				GpiMode,
				vgp3000c01v1Gpo7RGpi4Mode
				GpiMode,
				vgp3000c01v1Gpo7RGpi5Mode
				GpiMode,
				vgp3000c01v1Gpo7RGpi6Mode
				GpiMode,
				vgp3000c01v1Gpo7RGpi7Mode
				GpiMode,
				vgp3000c01v1Gpo7RGpi8Mode
				GpiMode,
				vgp3000c01v1Gpo7RDelay
				TimeX10Ms,
				vgp3000c01v1Gpo7RF
				Bit0And1Or,
				vgp3000c01v1Gpo8SGpi1Ena
				Bit0No1Yes,
				vgp3000c01v1Gpo8SGpi2Ena
				Bit0No1Yes,
				vgp3000c01v1Gpo8SGpi3Ena
				Bit0No1Yes,
				vgp3000c01v1Gpo8SGpi4Ena
				Bit0No1Yes,
				vgp3000c01v1Gpo8SGpi5Ena
				Bit0No1Yes,
				vgp3000c01v1Gpo8SGpi6Ena
				Bit0No1Yes,
				vgp3000c01v1Gpo8SGpi7Ena
				Bit0No1Yes,
				vgp3000c01v1Gpo8SGpi8Ena
				Bit0No1Yes,
				vgp3000c01v1Gpo8SGpi1Mode
				GpiMode,
				vgp3000c01v1Gpo8SGpi2Mode
				GpiMode,
				vgp3000c01v1Gpo8SGpi3Mode
				GpiMode,
				vgp3000c01v1Gpo8SGpi4Mode
				GpiMode,
				vgp3000c01v1Gpo8SGpi5Mode
				GpiMode,
				vgp3000c01v1Gpo8SGpi6Mode
				GpiMode,
				vgp3000c01v1Gpo8SGpi7Mode
				GpiMode,
				vgp3000c01v1Gpo8SGpi8Mode
				GpiMode,
				vgp3000c01v1Gpo8SDelay
				TimeX10Ms,
				vgp3000c01v1Gpo8SF
				Bit0And1Or,
				vgp3000c01v1Gpo8RGpi1Ena
				Bit0No1Yes,
				vgp3000c01v1Gpo8RGpi2Ena
				Bit0No1Yes,
				vgp3000c01v1Gpo8RGpi3Ena
				Bit0No1Yes,
				vgp3000c01v1Gpo8RGpi4Ena
				Bit0No1Yes,
				vgp3000c01v1Gpo8RGpi5Ena
				Bit0No1Yes,
				vgp3000c01v1Gpo8RGpi6Ena
				Bit0No1Yes,
				vgp3000c01v1Gpo8RGpi7Ena
				Bit0No1Yes,
				vgp3000c01v1Gpo8RGpi8Ena
				Bit0No1Yes,
				vgp3000c01v1Gpo8RGpi1Mode
				GpiMode,
				vgp3000c01v1Gpo8RGpi2Mode
				GpiMode,
				vgp3000c01v1Gpo8RGpi3Mode
				GpiMode,
				vgp3000c01v1Gpo8RGpi4Mode
				GpiMode,
				vgp3000c01v1Gpo8RGpi5Mode
				GpiMode,
				vgp3000c01v1Gpo8RGpi6Mode
				GpiMode,
				vgp3000c01v1Gpo8RGpi7Mode
				GpiMode,
				vgp3000c01v1Gpo8RGpi8Mode
				GpiMode,
				vgp3000c01v1Gpo8RDelay
				TimeX10Ms,
				vgp3000c01v1Gpo8RF
				Bit0And1Or,
				vgp3000c01v1Gpi1
				Bit0Open1Clo,
				vgp3000c01v1Gpi1TrapEnable
				AlarmEnable,
				vgp3000c01v1Gpi2
				Bit0Open1Clo,
				vgp3000c01v1Gpi2TrapEnable
				AlarmEnable,
				vgp3000c01v1Gpi3
				Bit0Open1Clo,
				vgp3000c01v1Gpi3TrapEnable
				AlarmEnable,
				vgp3000c01v1Gpi4
				Bit0Open1Clo,
				vgp3000c01v1Gpi4TrapEnable
				AlarmEnable,
				vgp3000c01v1Gpi5
				Bit0Open1Clo,
				vgp3000c01v1Gpi5TrapEnable
				AlarmEnable,
				vgp3000c01v1Gpi6
				Bit0Open1Clo,
				vgp3000c01v1Gpi6TrapEnable
				AlarmEnable,
				vgp3000c01v1Gpi7
				Bit0Open1Clo,
				vgp3000c01v1Gpi7TrapEnable
				AlarmEnable,
				vgp3000c01v1Gpi8
				Bit0Open1Clo,
				vgp3000c01v1Gpi8TrapEnable
				AlarmEnable,
				vgp3000c01v1Gpo1
				Bit0Open1Clo,
				vgp3000c01v1Gpo1TrapEnable
				AlarmEnable,
				vgp3000c01v1Gpo2
				Bit0Open1Clo,
				vgp3000c01v1Gpo2TrapEnable
				AlarmEnable,
				vgp3000c01v1Gpo3
				Bit0Open1Clo,
				vgp3000c01v1Gpo3TrapEnable
				AlarmEnable,
				vgp3000c01v1Gpo4
				Bit0Open1Clo,
				vgp3000c01v1Gpo4TrapEnable
				AlarmEnable,
				vgp3000c01v1Gpo5
				Bit0Open1Clo,
				vgp3000c01v1Gpo5TrapEnable
				AlarmEnable,
				vgp3000c01v1Gpo6
				Bit0Open1Clo,
				vgp3000c01v1Gpo6TrapEnable
				AlarmEnable,
				vgp3000c01v1Gpo7
				Bit0Open1Clo,
				vgp3000c01v1Gpo7TrapEnable
				AlarmEnable,
				vgp3000c01v1Gpo8
				Bit0Open1Clo,
				vgp3000c01v1Gpo8TrapEnable
				AlarmEnable,
				vgp3000c01v1SerialNo
				SerialNo
			 }

		-- 1.3.6.1.4.1.10106.3.101291.1.1.1
		vgp3000c01v1Index OBJECT-TYPE
			SYNTAX ModuleIndex
			MAX-ACCESS read-only
			STATUS current
			DESCRIPTION
				"Index of VGP3000C01V1 Table"
		::= { vgp3000c01v1Entry 1 }

		-- 1.3.6.1.4.1.10106.3.101291.1.1.3
		vgp3000c01v1GpioStatMode OBJECT-TYPE
			SYNTAX Bit0No1Yes
			MAX-ACCESS read-write
			STATUS current
			DESCRIPTION
				"Allows holding status and led info for at least 1 s"
		::= { vgp3000c01v1Entry 3 }

		-- 1.3.6.1.4.1.10106.3.101291.1.1.5
		vgp3000c01v1Gpo1SGpi1Ena OBJECT-TYPE
			SYNTAX Bit0No1Yes
			MAX-ACCESS read-write
			STATUS current
			DESCRIPTION
				"Enables the GPI1 input to be used in the SET function"
		::= { vgp3000c01v1Entry 5 }

		-- 1.3.6.1.4.1.10106.3.101291.1.1.7
		vgp3000c01v1Gpo1SGpi2Ena OBJECT-TYPE
			SYNTAX Bit0No1Yes
			MAX-ACCESS read-write
			STATUS current
			DESCRIPTION
				"Enables the GPI2 input to be used in the SET function"
		::= { vgp3000c01v1Entry 7 }

		-- 1.3.6.1.4.1.10106.3.101291.1.1.9
		vgp3000c01v1Gpo1SGpi3Ena OBJECT-TYPE
			SYNTAX Bit0No1Yes
			MAX-ACCESS read-write
			STATUS current
			DESCRIPTION
				"Enables the GPI3 input to be used in the SET function"
		::= { vgp3000c01v1Entry 9 }

		-- 1.3.6.1.4.1.10106.3.101291.1.1.11
		vgp3000c01v1Gpo1SGpi4Ena OBJECT-TYPE
			SYNTAX Bit0No1Yes
			MAX-ACCESS read-write
			STATUS current
			DESCRIPTION
				"Enables the GPI4 input to be used in the SET function"
		::= { vgp3000c01v1Entry 11 }

		-- 1.3.6.1.4.1.10106.3.101291.1.1.13
		vgp3000c01v1Gpo1SGpi5Ena OBJECT-TYPE
			SYNTAX Bit0No1Yes
			MAX-ACCESS read-write
			STATUS current
			DESCRIPTION
				"Enables the GPI5 input to be used in the SET function"
		::= { vgp3000c01v1Entry 13 }

		-- 1.3.6.1.4.1.10106.3.101291.1.1.15
		vgp3000c01v1Gpo1SGpi6Ena OBJECT-TYPE
			SYNTAX Bit0No1Yes
			MAX-ACCESS read-write
			STATUS current
			DESCRIPTION
				"Enables the GPI6 input to be used in the SET function"
		::= { vgp3000c01v1Entry 15 }

		-- 1.3.6.1.4.1.10106.3.101291.1.1.17
		vgp3000c01v1Gpo1SGpi7Ena OBJECT-TYPE
			SYNTAX Bit0No1Yes
			MAX-ACCESS read-write
			STATUS current
			DESCRIPTION
				"Enables the GPI7 input to be used in the SET function"
		::= { vgp3000c01v1Entry 17 }

		-- 1.3.6.1.4.1.10106.3.101291.1.1.19
		vgp3000c01v1Gpo1SGpi8Ena OBJECT-TYPE
			SYNTAX Bit0No1Yes
			MAX-ACCESS read-write
			STATUS current
			DESCRIPTION
				"Enables the GPI8 input to be used in the SET function"
		::= { vgp3000c01v1Entry 19 }

		-- 1.3.6.1.4.1.10106.3.101291.1.1.21
		vgp3000c01v1Gpo1SGpi1Mode OBJECT-TYPE
			SYNTAX GpiMode
			MAX-ACCESS read-write
			STATUS current
			DESCRIPTION
				"Allows selecting the mode of GPI1 input in the SET function"
		::= { vgp3000c01v1Entry 21 }

		-- 1.3.6.1.4.1.10106.3.101291.1.1.23
		vgp3000c01v1Gpo1SGpi2Mode OBJECT-TYPE
			SYNTAX GpiMode
			MAX-ACCESS read-write
			STATUS current
			DESCRIPTION
				"Allows selecting the mode of GPI2 input in the SET function"
		::= { vgp3000c01v1Entry 23 }

		-- 1.3.6.1.4.1.10106.3.101291.1.1.25
		vgp3000c01v1Gpo1SGpi3Mode OBJECT-TYPE
			SYNTAX GpiMode
			MAX-ACCESS read-write
			STATUS current
			DESCRIPTION
				"Allows selecting the mode of GPI3 input in the SET function"
		::= { vgp3000c01v1Entry 25 }

		-- 1.3.6.1.4.1.10106.3.101291.1.1.27
		vgp3000c01v1Gpo1SGpi4Mode OBJECT-TYPE
			SYNTAX GpiMode
			MAX-ACCESS read-write
			STATUS current
			DESCRIPTION
				"Allows selecting the mode of GPI4 input in the SET function"
		::= { vgp3000c01v1Entry 27 }

		-- 1.3.6.1.4.1.10106.3.101291.1.1.29
		vgp3000c01v1Gpo1SGpi5Mode OBJECT-TYPE
			SYNTAX GpiMode
			MAX-ACCESS read-write
			STATUS current
			DESCRIPTION
				"Allows selecting the mode of GPI5 input in the SET function"
		::= { vgp3000c01v1Entry 29 }

		-- 1.3.6.1.4.1.10106.3.101291.1.1.31
		vgp3000c01v1Gpo1SGpi6Mode OBJECT-TYPE
			SYNTAX GpiMode
			MAX-ACCESS read-write
			STATUS current
			DESCRIPTION
				"Allows selecting the mode of GPI6 input in the SET function"
		::= { vgp3000c01v1Entry 31 }

		-- 1.3.6.1.4.1.10106.3.101291.1.1.33
		vgp3000c01v1Gpo1SGpi7Mode OBJECT-TYPE
			SYNTAX GpiMode
			MAX-ACCESS read-write
			STATUS current
			DESCRIPTION
				"Allows selecting the mode of GPI7 input in the SET function"
		::= { vgp3000c01v1Entry 33 }

		-- 1.3.6.1.4.1.10106.3.101291.1.1.35
		vgp3000c01v1Gpo1SGpi8Mode OBJECT-TYPE
			SYNTAX GpiMode
			MAX-ACCESS read-write
			STATUS current
			DESCRIPTION
				"Allows selecting the mode of GPI8 input in the SET function"
		::= { vgp3000c01v1Entry 35 }

		-- 1.3.6.1.4.1.10106.3.101291.1.1.37
		vgp3000c01v1Gpo1SDelay OBJECT-TYPE
			SYNTAX TimeX10Ms
			MAX-ACCESS read-write
			STATUS current
			DESCRIPTION
				"Allows adjusting the delay in SET function"
		::= { vgp3000c01v1Entry 37 }

		-- 1.3.6.1.4.1.10106.3.101291.1.1.39
		vgp3000c01v1Gpo1SF OBJECT-TYPE
			SYNTAX Bit0And1Or
			MAX-ACCESS read-write
			STATUS current
			DESCRIPTION
				"Allows selecting the type of the SET function"
		::= { vgp3000c01v1Entry 39 }

		-- 1.3.6.1.4.1.10106.3.101291.1.1.41
		vgp3000c01v1Gpo1RGpi1Ena OBJECT-TYPE
			SYNTAX Bit0No1Yes
			MAX-ACCESS read-write
			STATUS current
			DESCRIPTION
				"Enables the GPI1 input to be used in the RESET function"
		::= { vgp3000c01v1Entry 41 }

		-- 1.3.6.1.4.1.10106.3.101291.1.1.43
		vgp3000c01v1Gpo1RGpi2Ena OBJECT-TYPE
			SYNTAX Bit0No1Yes
			MAX-ACCESS read-write
			STATUS current
			DESCRIPTION
				"Enables the GPI2 input to be used in the RESET function"
		::= { vgp3000c01v1Entry 43 }

		-- 1.3.6.1.4.1.10106.3.101291.1.1.45
		vgp3000c01v1Gpo1RGpi3Ena OBJECT-TYPE
			SYNTAX Bit0No1Yes
			MAX-ACCESS read-write
			STATUS current
			DESCRIPTION
				"Enables the GPI3 input to be used in the RESET function"
		::= { vgp3000c01v1Entry 45 }

		-- 1.3.6.1.4.1.10106.3.101291.1.1.47
		vgp3000c01v1Gpo1RGpi4Ena OBJECT-TYPE
			SYNTAX Bit0No1Yes
			MAX-ACCESS read-write
			STATUS current
			DESCRIPTION
				"Enables the GPI4 input to be used in the RESET function"
		::= { vgp3000c01v1Entry 47 }

		-- 1.3.6.1.4.1.10106.3.101291.1.1.49
		vgp3000c01v1Gpo1RGpi5Ena OBJECT-TYPE
			SYNTAX Bit0No1Yes
			MAX-ACCESS read-write
			STATUS current
			DESCRIPTION
				"Enables the GPI5 input to be used in the RESET function"
		::= { vgp3000c01v1Entry 49 }

		-- 1.3.6.1.4.1.10106.3.101291.1.1.51
		vgp3000c01v1Gpo1RGpi6Ena OBJECT-TYPE
			SYNTAX Bit0No1Yes
			MAX-ACCESS read-write
			STATUS current
			DESCRIPTION
				"Enables the GPI6 input to be used in the RESET function"
		::= { vgp3000c01v1Entry 51 }

		-- 1.3.6.1.4.1.10106.3.101291.1.1.53
		vgp3000c01v1Gpo1RGpi7Ena OBJECT-TYPE
			SYNTAX Bit0No1Yes
			MAX-ACCESS read-write
			STATUS current
			DESCRIPTION
				"Enables the GPI7 input to be used in the RESET function"
		::= { vgp3000c01v1Entry 53 }

		-- 1.3.6.1.4.1.10106.3.101291.1.1.55
		vgp3000c01v1Gpo1RGpi8Ena OBJECT-TYPE
			SYNTAX Bit0No1Yes
			MAX-ACCESS read-write
			STATUS current
			DESCRIPTION
				"Enables the GPI8 input to be used in the RESET function"
		::= { vgp3000c01v1Entry 55 }

		-- 1.3.6.1.4.1.10106.3.101291.1.1.57
		vgp3000c01v1Gpo1RGpi1Mode OBJECT-TYPE
			SYNTAX GpiMode
			MAX-ACCESS read-write
			STATUS current
			DESCRIPTION
				"Allows selecting the mode of GPI1 input in the RESET function"
		::= { vgp3000c01v1Entry 57 }

		-- 1.3.6.1.4.1.10106.3.101291.1.1.59
		vgp3000c01v1Gpo1RGpi2Mode OBJECT-TYPE
			SYNTAX GpiMode
			MAX-ACCESS read-write
			STATUS current
			DESCRIPTION
				"Allows selecting the mode of GPI2 input in the RESET function"
		::= { vgp3000c01v1Entry 59 }

		-- 1.3.6.1.4.1.10106.3.101291.1.1.61
		vgp3000c01v1Gpo1RGpi3Mode OBJECT-TYPE
			SYNTAX GpiMode
			MAX-ACCESS read-write
			STATUS current
			DESCRIPTION
				"Allows selecting the mode of GPI3 input in the RESET function"
		::= { vgp3000c01v1Entry 61 }

		-- 1.3.6.1.4.1.10106.3.101291.1.1.63
		vgp3000c01v1Gpo1RGpi4Mode OBJECT-TYPE
			SYNTAX GpiMode
			MAX-ACCESS read-write
			STATUS current
			DESCRIPTION
				"Allows selecting the mode of GPI4 input in the RESET function"
		::= { vgp3000c01v1Entry 63 }

		-- 1.3.6.1.4.1.10106.3.101291.1.1.65
		vgp3000c01v1Gpo1RGpi5Mode OBJECT-TYPE
			SYNTAX GpiMode
			MAX-ACCESS read-write
			STATUS current
			DESCRIPTION
				"Allows selecting the mode of GPI5 input in the RESET function"
		::= { vgp3000c01v1Entry 65 }

		-- 1.3.6.1.4.1.10106.3.101291.1.1.67
		vgp3000c01v1Gpo1RGpi6Mode OBJECT-TYPE
			SYNTAX GpiMode
			MAX-ACCESS read-write
			STATUS current
			DESCRIPTION
				"Allows selecting the mode of GPI6 input in the RESET function"
		::= { vgp3000c01v1Entry 67 }

		-- 1.3.6.1.4.1.10106.3.101291.1.1.69
		vgp3000c01v1Gpo1RGpi7Mode OBJECT-TYPE
			SYNTAX GpiMode
			MAX-ACCESS read-write
			STATUS current
			DESCRIPTION
				"Allows selecting the mode of GPI7 input in the RESET function"
		::= { vgp3000c01v1Entry 69 }

		-- 1.3.6.1.4.1.10106.3.101291.1.1.71
		vgp3000c01v1Gpo1RGpi8Mode OBJECT-TYPE
			SYNTAX GpiMode
			MAX-ACCESS read-write
			STATUS current
			DESCRIPTION
				"Allows selecting the mode of GPI8 input in the RESET function"
		::= { vgp3000c01v1Entry 71 }

		-- 1.3.6.1.4.1.10106.3.101291.1.1.73
		vgp3000c01v1Gpo1RDelay OBJECT-TYPE
			SYNTAX TimeX10Ms
			MAX-ACCESS read-write
			STATUS current
			DESCRIPTION
				"Allows adjusting the delay in RESET function"
		::= { vgp3000c01v1Entry 73 }

		-- 1.3.6.1.4.1.10106.3.101291.1.1.75
		vgp3000c01v1Gpo1RF OBJECT-TYPE
			SYNTAX Bit0And1Or
			MAX-ACCESS read-write
			STATUS current
			DESCRIPTION
				"Allows selecting the type of the RESET function"
		::= { vgp3000c01v1Entry 75 }

		-- 1.3.6.1.4.1.10106.3.101291.1.1.77
		vgp3000c01v1Gpo2SGpi1Ena OBJECT-TYPE
			SYNTAX Bit0No1Yes
			MAX-ACCESS read-write
			STATUS current
			DESCRIPTION
				"Enables the GPI1 input to be used in the SET function"
		::= { vgp3000c01v1Entry 77 }

		-- 1.3.6.1.4.1.10106.3.101291.1.1.79
		vgp3000c01v1Gpo2SGpi2Ena OBJECT-TYPE
			SYNTAX Bit0No1Yes
			MAX-ACCESS read-write
			STATUS current
			DESCRIPTION
				"Enables the GPI2 input to be used in the SET function"
		::= { vgp3000c01v1Entry 79 }

		-- 1.3.6.1.4.1.10106.3.101291.1.1.81
		vgp3000c01v1Gpo2SGpi3Ena OBJECT-TYPE
			SYNTAX Bit0No1Yes
			MAX-ACCESS read-write
			STATUS current
			DESCRIPTION
				"Enables the GPI3 input to be used in the SET function"
		::= { vgp3000c01v1Entry 81 }

		-- 1.3.6.1.4.1.10106.3.101291.1.1.83
		vgp3000c01v1Gpo2SGpi4Ena OBJECT-TYPE
			SYNTAX Bit0No1Yes
			MAX-ACCESS read-write
			STATUS current
			DESCRIPTION
				"Enables the GPI4 input to be used in the SET function"
		::= { vgp3000c01v1Entry 83 }

		-- 1.3.6.1.4.1.10106.3.101291.1.1.85
		vgp3000c01v1Gpo2SGpi5Ena OBJECT-TYPE
			SYNTAX Bit0No1Yes
			MAX-ACCESS read-write
			STATUS current
			DESCRIPTION
				"Enables the GPI5 input to be used in the SET function"
		::= { vgp3000c01v1Entry 85 }

		-- 1.3.6.1.4.1.10106.3.101291.1.1.87
		vgp3000c01v1Gpo2SGpi6Ena OBJECT-TYPE
			SYNTAX Bit0No1Yes
			MAX-ACCESS read-write
			STATUS current
			DESCRIPTION
				"Enables the GPI6 input to be used in the SET function"
		::= { vgp3000c01v1Entry 87 }

		-- 1.3.6.1.4.1.10106.3.101291.1.1.89
		vgp3000c01v1Gpo2SGpi7Ena OBJECT-TYPE
			SYNTAX Bit0No1Yes
			MAX-ACCESS read-write
			STATUS current
			DESCRIPTION
				"Enables the GPI7 input to be used in the SET function"
		::= { vgp3000c01v1Entry 89 }

		-- 1.3.6.1.4.1.10106.3.101291.1.1.91
		vgp3000c01v1Gpo2SGpi8Ena OBJECT-TYPE
			SYNTAX Bit0No1Yes
			MAX-ACCESS read-write
			STATUS current
			DESCRIPTION
				"Enables the GPI8 input to be used in the SET function"
		::= { vgp3000c01v1Entry 91 }

		-- 1.3.6.1.4.1.10106.3.101291.1.1.93
		vgp3000c01v1Gpo2SGpi1Mode OBJECT-TYPE
			SYNTAX GpiMode
			MAX-ACCESS read-write
			STATUS current
			DESCRIPTION
				"Allows selecting the mode of GPI1 input in the SET function"
		::= { vgp3000c01v1Entry 93 }

		-- 1.3.6.1.4.1.10106.3.101291.1.1.95
		vgp3000c01v1Gpo2SGpi2Mode OBJECT-TYPE
			SYNTAX GpiMode
			MAX-ACCESS read-write
			STATUS current
			DESCRIPTION
				"Allows selecting the mode of GPI2 input in the SET function"
		::= { vgp3000c01v1Entry 95 }

		-- 1.3.6.1.4.1.10106.3.101291.1.1.97
		vgp3000c01v1Gpo2SGpi3Mode OBJECT-TYPE
			SYNTAX GpiMode
			MAX-ACCESS read-write
			STATUS current
			DESCRIPTION
				"Allows selecting the mode of GPI3 input in the SET function"
		::= { vgp3000c01v1Entry 97 }

		-- 1.3.6.1.4.1.10106.3.101291.1.1.99
		vgp3000c01v1Gpo2SGpi4Mode OBJECT-TYPE
			SYNTAX GpiMode
			MAX-ACCESS read-write
			STATUS current
			DESCRIPTION
				"Allows selecting the mode of GPI4 input in the SET function"
		::= { vgp3000c01v1Entry 99 }

		-- 1.3.6.1.4.1.10106.3.101291.1.1.101
		vgp3000c01v1Gpo2SGpi5Mode OBJECT-TYPE
			SYNTAX GpiMode
			MAX-ACCESS read-write
			STATUS current
			DESCRIPTION
				"Allows selecting the mode of GPI5 input in the SET function"
		::= { vgp3000c01v1Entry 101 }

		-- 1.3.6.1.4.1.10106.3.101291.1.1.103
		vgp3000c01v1Gpo2SGpi6Mode OBJECT-TYPE
			SYNTAX GpiMode
			MAX-ACCESS read-write
			STATUS current
			DESCRIPTION
				"Allows selecting the mode of GPI6 input in the SET function"
		::= { vgp3000c01v1Entry 103 }

		-- 1.3.6.1.4.1.10106.3.101291.1.1.105
		vgp3000c01v1Gpo2SGpi7Mode OBJECT-TYPE
			SYNTAX GpiMode
			MAX-ACCESS read-write
			STATUS current
			DESCRIPTION
				"Allows selecting the mode of GPI7 input in the SET function"
		::= { vgp3000c01v1Entry 105 }

		-- 1.3.6.1.4.1.10106.3.101291.1.1.107
		vgp3000c01v1Gpo2SGpi8Mode OBJECT-TYPE
			SYNTAX GpiMode
			MAX-ACCESS read-write
			STATUS current
			DESCRIPTION
				"Allows selecting the mode of GPI8 input in the SET function"
		::= { vgp3000c01v1Entry 107 }

		-- 1.3.6.1.4.1.10106.3.101291.1.1.109
		vgp3000c01v1Gpo2SDelay OBJECT-TYPE
			SYNTAX TimeX10Ms
			MAX-ACCESS read-write
			STATUS current
			DESCRIPTION
				"Allows adjusting the delay in SET function"
		::= { vgp3000c01v1Entry 109 }

		-- 1.3.6.1.4.1.10106.3.101291.1.1.111
		vgp3000c01v1Gpo2SF OBJECT-TYPE
			SYNTAX Bit0And1Or
			MAX-ACCESS read-write
			STATUS current
			DESCRIPTION
				"Allows selecting the type of the SET function"
		::= { vgp3000c01v1Entry 111 }

		-- 1.3.6.1.4.1.10106.3.101291.1.1.113
		vgp3000c01v1Gpo2RGpi1Ena OBJECT-TYPE
			SYNTAX Bit0No1Yes
			MAX-ACCESS read-write
			STATUS current
			DESCRIPTION
				"Enables the GPI1 input to be used in the RESET function"
		::= { vgp3000c01v1Entry 113 }

		-- 1.3.6.1.4.1.10106.3.101291.1.1.115
		vgp3000c01v1Gpo2RGpi2Ena OBJECT-TYPE
			SYNTAX Bit0No1Yes
			MAX-ACCESS read-write
			STATUS current
			DESCRIPTION
				"Enables the GPI2 input to be used in the RESET function"
		::= { vgp3000c01v1Entry 115 }

		-- 1.3.6.1.4.1.10106.3.101291.1.1.117
		vgp3000c01v1Gpo2RGpi3Ena OBJECT-TYPE
			SYNTAX Bit0No1Yes
			MAX-ACCESS read-write
			STATUS current
			DESCRIPTION
				"Enables the GPI3 input to be used in the RESET function"
		::= { vgp3000c01v1Entry 117 }

		-- 1.3.6.1.4.1.10106.3.101291.1.1.119
		vgp3000c01v1Gpo2RGpi4Ena OBJECT-TYPE
			SYNTAX Bit0No1Yes
			MAX-ACCESS read-write
			STATUS current
			DESCRIPTION
				"Enables the GPI4 input to be used in the RESET function"
		::= { vgp3000c01v1Entry 119 }

		-- 1.3.6.1.4.1.10106.3.101291.1.1.121
		vgp3000c01v1Gpo2RGpi5Ena OBJECT-TYPE
			SYNTAX Bit0No1Yes
			MAX-ACCESS read-write
			STATUS current
			DESCRIPTION
				"Enables the GPI5 input to be used in the RESET function"
		::= { vgp3000c01v1Entry 121 }

		-- 1.3.6.1.4.1.10106.3.101291.1.1.123
		vgp3000c01v1Gpo2RGpi6Ena OBJECT-TYPE
			SYNTAX Bit0No1Yes
			MAX-ACCESS read-write
			STATUS current
			DESCRIPTION
				"Enables the GPI6 input to be used in the RESET function"
		::= { vgp3000c01v1Entry 123 }

		-- 1.3.6.1.4.1.10106.3.101291.1.1.125
		vgp3000c01v1Gpo2RGpi7Ena OBJECT-TYPE
			SYNTAX Bit0No1Yes
			MAX-ACCESS read-write
			STATUS current
			DESCRIPTION
				"Enables the GPI7 input to be used in the RESET function"
		::= { vgp3000c01v1Entry 125 }

		-- 1.3.6.1.4.1.10106.3.101291.1.1.127
		vgp3000c01v1Gpo2RGpi8Ena OBJECT-TYPE
			SYNTAX Bit0No1Yes
			MAX-ACCESS read-write
			STATUS current
			DESCRIPTION
				"Enables the GPI8 input to be used in the RESET function"
		::= { vgp3000c01v1Entry 127 }

		-- 1.3.6.1.4.1.10106.3.101291.1.1.129
		vgp3000c01v1Gpo2RGpi1Mode OBJECT-TYPE
			SYNTAX GpiMode
			MAX-ACCESS read-write
			STATUS current
			DESCRIPTION
				"Allows selecting the mode of GPI1 input in the RESET function"
		::= { vgp3000c01v1Entry 129 }

		-- 1.3.6.1.4.1.10106.3.101291.1.1.131
		vgp3000c01v1Gpo2RGpi2Mode OBJECT-TYPE
			SYNTAX GpiMode
			MAX-ACCESS read-write
			STATUS current
			DESCRIPTION
				"Allows selecting the mode of GPI2 input in the RESET function"
		::= { vgp3000c01v1Entry 131 }

		-- 1.3.6.1.4.1.10106.3.101291.1.1.133
		vgp3000c01v1Gpo2RGpi3Mode OBJECT-TYPE
			SYNTAX GpiMode
			MAX-ACCESS read-write
			STATUS current
			DESCRIPTION
				"Allows selecting the mode of GPI3 input in the RESET function"
		::= { vgp3000c01v1Entry 133 }

		-- 1.3.6.1.4.1.10106.3.101291.1.1.135
		vgp3000c01v1Gpo2RGpi4Mode OBJECT-TYPE
			SYNTAX GpiMode
			MAX-ACCESS read-write
			STATUS current
			DESCRIPTION
				"Allows selecting the mode of GPI4 input in the RESET function"
		::= { vgp3000c01v1Entry 135 }

		-- 1.3.6.1.4.1.10106.3.101291.1.1.137
		vgp3000c01v1Gpo2RGpi5Mode OBJECT-TYPE
			SYNTAX GpiMode
			MAX-ACCESS read-write
			STATUS current
			DESCRIPTION
				"Allows selecting the mode of GPI5 input in the RESET function"
		::= { vgp3000c01v1Entry 137 }

		-- 1.3.6.1.4.1.10106.3.101291.1.1.139
		vgp3000c01v1Gpo2RGpi6Mode OBJECT-TYPE
			SYNTAX GpiMode
			MAX-ACCESS read-write
			STATUS current
			DESCRIPTION
				"Allows selecting the mode of GPI6 input in the RESET function"
		::= { vgp3000c01v1Entry 139 }

		-- 1.3.6.1.4.1.10106.3.101291.1.1.141
		vgp3000c01v1Gpo2RGpi7Mode OBJECT-TYPE
			SYNTAX GpiMode
			MAX-ACCESS read-write
			STATUS current
			DESCRIPTION
				"Allows selecting the mode of GPI7 input in the RESET function"
		::= { vgp3000c01v1Entry 141 }

		-- 1.3.6.1.4.1.10106.3.101291.1.1.143
		vgp3000c01v1Gpo2RGpi8Mode OBJECT-TYPE
			SYNTAX GpiMode
			MAX-ACCESS read-write
			STATUS current
			DESCRIPTION
				"Allows selecting the mode of GPI8 input in the RESET function"
		::= { vgp3000c01v1Entry 143 }

		-- 1.3.6.1.4.1.10106.3.101291.1.1.145
		vgp3000c01v1Gpo2RDelay OBJECT-TYPE
			SYNTAX TimeX10Ms
			MAX-ACCESS read-write
			STATUS current
			DESCRIPTION
				"Allows adjusting the delay in RESET function"
		::= { vgp3000c01v1Entry 145 }

		-- 1.3.6.1.4.1.10106.3.101291.1.1.147
		vgp3000c01v1Gpo2RF OBJECT-TYPE
			SYNTAX Bit0And1Or
			MAX-ACCESS read-write
			STATUS current
			DESCRIPTION
				"Allows selecting the type of the RESET function"
		::= { vgp3000c01v1Entry 147 }

		-- 1.3.6.1.4.1.10106.3.101291.1.1.149
		vgp3000c01v1Gpo3SGpi1Ena OBJECT-TYPE
			SYNTAX Bit0No1Yes
			MAX-ACCESS read-write
			STATUS current
			DESCRIPTION
				"Enables the GPI1 input to be used in the SET function"
		::= { vgp3000c01v1Entry 149 }

		-- 1.3.6.1.4.1.10106.3.101291.1.1.151
		vgp3000c01v1Gpo3SGpi2Ena OBJECT-TYPE
			SYNTAX Bit0No1Yes
			MAX-ACCESS read-write
			STATUS current
			DESCRIPTION
				"Enables the GPI2 input to be used in the SET function"
		::= { vgp3000c01v1Entry 151 }

		-- 1.3.6.1.4.1.10106.3.101291.1.1.153
		vgp3000c01v1Gpo3SGpi3Ena OBJECT-TYPE
			SYNTAX Bit0No1Yes
			MAX-ACCESS read-write
			STATUS current
			DESCRIPTION
				"Enables the GPI3 input to be used in the SET function"
		::= { vgp3000c01v1Entry 153 }

		-- 1.3.6.1.4.1.10106.3.101291.1.1.155
		vgp3000c01v1Gpo3SGpi4Ena OBJECT-TYPE
			SYNTAX Bit0No1Yes
			MAX-ACCESS read-write
			STATUS current
			DESCRIPTION
				"Enables the GPI4 input to be used in the SET function"
		::= { vgp3000c01v1Entry 155 }

		-- 1.3.6.1.4.1.10106.3.101291.1.1.157
		vgp3000c01v1Gpo3SGpi5Ena OBJECT-TYPE
			SYNTAX Bit0No1Yes
			MAX-ACCESS read-write
			STATUS current
			DESCRIPTION
				"Enables the GPI5 input to be used in the SET function"
		::= { vgp3000c01v1Entry 157 }

		-- 1.3.6.1.4.1.10106.3.101291.1.1.159
		vgp3000c01v1Gpo3SGpi6Ena OBJECT-TYPE
			SYNTAX Bit0No1Yes
			MAX-ACCESS read-write
			STATUS current
			DESCRIPTION
				"Enables the GPI6 input to be used in the SET function"
		::= { vgp3000c01v1Entry 159 }

		-- 1.3.6.1.4.1.10106.3.101291.1.1.161
		vgp3000c01v1Gpo3SGpi7Ena OBJECT-TYPE
			SYNTAX Bit0No1Yes
			MAX-ACCESS read-write
			STATUS current
			DESCRIPTION
				"Enables the GPI7 input to be used in the SET function"
		::= { vgp3000c01v1Entry 161 }

		-- 1.3.6.1.4.1.10106.3.101291.1.1.163
		vgp3000c01v1Gpo3SGpi8Ena OBJECT-TYPE
			SYNTAX Bit0No1Yes
			MAX-ACCESS read-write
			STATUS current
			DESCRIPTION
				"Enables the GPI8 input to be used in the SET function"
		::= { vgp3000c01v1Entry 163 }

		-- 1.3.6.1.4.1.10106.3.101291.1.1.165
		vgp3000c01v1Gpo3SGpi1Mode OBJECT-TYPE
			SYNTAX GpiMode
			MAX-ACCESS read-write
			STATUS current
			DESCRIPTION
				"Allows selecting the mode of GPI1 input in the SET function"
		::= { vgp3000c01v1Entry 165 }

		-- 1.3.6.1.4.1.10106.3.101291.1.1.167
		vgp3000c01v1Gpo3SGpi2Mode OBJECT-TYPE
			SYNTAX GpiMode
			MAX-ACCESS read-write
			STATUS current
			DESCRIPTION
				"Allows selecting the mode of GPI2 input in the SET function"
		::= { vgp3000c01v1Entry 167 }

		-- 1.3.6.1.4.1.10106.3.101291.1.1.169
		vgp3000c01v1Gpo3SGpi3Mode OBJECT-TYPE
			SYNTAX GpiMode
			MAX-ACCESS read-write
			STATUS current
			DESCRIPTION
				"Allows selecting the mode of GPI3 input in the SET function"
		::= { vgp3000c01v1Entry 169 }

		-- 1.3.6.1.4.1.10106.3.101291.1.1.171
		vgp3000c01v1Gpo3SGpi4Mode OBJECT-TYPE
			SYNTAX GpiMode
			MAX-ACCESS read-write
			STATUS current
			DESCRIPTION
				"Allows selecting the mode of GPI4 input in the SET function"
		::= { vgp3000c01v1Entry 171 }

		-- 1.3.6.1.4.1.10106.3.101291.1.1.173
		vgp3000c01v1Gpo3SGpi5Mode OBJECT-TYPE
			SYNTAX GpiMode
			MAX-ACCESS read-write
			STATUS current
			DESCRIPTION
				"Allows selecting the mode of GPI5 input in the SET function"
		::= { vgp3000c01v1Entry 173 }

		-- 1.3.6.1.4.1.10106.3.101291.1.1.175
		vgp3000c01v1Gpo3SGpi6Mode OBJECT-TYPE
			SYNTAX GpiMode
			MAX-ACCESS read-write
			STATUS current
			DESCRIPTION
				"Allows selecting the mode of GPI6 input in the SET function"
		::= { vgp3000c01v1Entry 175 }

		-- 1.3.6.1.4.1.10106.3.101291.1.1.177
		vgp3000c01v1Gpo3SGpi7Mode OBJECT-TYPE
			SYNTAX GpiMode
			MAX-ACCESS read-write
			STATUS current
			DESCRIPTION
				"Allows selecting the mode of GPI7 input in the SET function"
		::= { vgp3000c01v1Entry 177 }

		-- 1.3.6.1.4.1.10106.3.101291.1.1.179
		vgp3000c01v1Gpo3SGpi8Mode OBJECT-TYPE
			SYNTAX GpiMode
			MAX-ACCESS read-write
			STATUS current
			DESCRIPTION
				"Allows selecting the mode of GPI8 input in the SET function"
		::= { vgp3000c01v1Entry 179 }

		-- 1.3.6.1.4.1.10106.3.101291.1.1.181
		vgp3000c01v1Gpo3SDelay OBJECT-TYPE
			SYNTAX TimeX10Ms
			MAX-ACCESS read-write
			STATUS current
			DESCRIPTION
				"Allows adjusting the delay in SET function"
		::= { vgp3000c01v1Entry 181 }

		-- 1.3.6.1.4.1.10106.3.101291.1.1.183
		vgp3000c01v1Gpo3SF OBJECT-TYPE
			SYNTAX Bit0And1Or
			MAX-ACCESS read-write
			STATUS current
			DESCRIPTION
				"Allows selecting the type of the SET function"
		::= { vgp3000c01v1Entry 183 }

		-- 1.3.6.1.4.1.10106.3.101291.1.1.185
		vgp3000c01v1Gpo3RGpi1Ena OBJECT-TYPE
			SYNTAX Bit0No1Yes
			MAX-ACCESS read-write
			STATUS current
			DESCRIPTION
				"Enables the GPI1 input to be used in the RESET function"
		::= { vgp3000c01v1Entry 185 }

		-- 1.3.6.1.4.1.10106.3.101291.1.1.187
		vgp3000c01v1Gpo3RGpi2Ena OBJECT-TYPE
			SYNTAX Bit0No1Yes
			MAX-ACCESS read-write
			STATUS current
			DESCRIPTION
				"Enables the GPI2 input to be used in the RESET function"
		::= { vgp3000c01v1Entry 187 }

		-- 1.3.6.1.4.1.10106.3.101291.1.1.189
		vgp3000c01v1Gpo3RGpi3Ena OBJECT-TYPE
			SYNTAX Bit0No1Yes
			MAX-ACCESS read-write
			STATUS current
			DESCRIPTION
				"Enables the GPI3 input to be used in the RESET function"
		::= { vgp3000c01v1Entry 189 }

		-- 1.3.6.1.4.1.10106.3.101291.1.1.191
		vgp3000c01v1Gpo3RGpi4Ena OBJECT-TYPE
			SYNTAX Bit0No1Yes
			MAX-ACCESS read-write
			STATUS current
			DESCRIPTION
				"Enables the GPI4 input to be used in the RESET function"
		::= { vgp3000c01v1Entry 191 }

		-- 1.3.6.1.4.1.10106.3.101291.1.1.193
		vgp3000c01v1Gpo3RGpi5Ena OBJECT-TYPE
			SYNTAX Bit0No1Yes
			MAX-ACCESS read-write
			STATUS current
			DESCRIPTION
				"Enables the GPI5 input to be used in the RESET function"
		::= { vgp3000c01v1Entry 193 }

		-- 1.3.6.1.4.1.10106.3.101291.1.1.195
		vgp3000c01v1Gpo3RGpi6Ena OBJECT-TYPE
			SYNTAX Bit0No1Yes
			MAX-ACCESS read-write
			STATUS current
			DESCRIPTION
				"Enables the GPI6 input to be used in the RESET function"
		::= { vgp3000c01v1Entry 195 }

		-- 1.3.6.1.4.1.10106.3.101291.1.1.197
		vgp3000c01v1Gpo3RGpi7Ena OBJECT-TYPE
			SYNTAX Bit0No1Yes
			MAX-ACCESS read-write
			STATUS current
			DESCRIPTION
				"Enables the GPI7 input to be used in the RESET function"
		::= { vgp3000c01v1Entry 197 }

		-- 1.3.6.1.4.1.10106.3.101291.1.1.199
		vgp3000c01v1Gpo3RGpi8Ena OBJECT-TYPE
			SYNTAX Bit0No1Yes
			MAX-ACCESS read-write
			STATUS current
			DESCRIPTION
				"Enables the GPI8 input to be used in the RESET function"
		::= { vgp3000c01v1Entry 199 }

		-- 1.3.6.1.4.1.10106.3.101291.1.1.201
		vgp3000c01v1Gpo3RGpi1Mode OBJECT-TYPE
			SYNTAX GpiMode
			MAX-ACCESS read-write
			STATUS current
			DESCRIPTION
				"Allows selecting the mode of GPI1 input in the RESET function"
		::= { vgp3000c01v1Entry 201 }

		-- 1.3.6.1.4.1.10106.3.101291.1.1.203
		vgp3000c01v1Gpo3RGpi2Mode OBJECT-TYPE
			SYNTAX GpiMode
			MAX-ACCESS read-write
			STATUS current
			DESCRIPTION
				"Allows selecting the mode of GPI2 input in the RESET function"
		::= { vgp3000c01v1Entry 203 }

		-- 1.3.6.1.4.1.10106.3.101291.1.1.205
		vgp3000c01v1Gpo3RGpi3Mode OBJECT-TYPE
			SYNTAX GpiMode
			MAX-ACCESS read-write
			STATUS current
			DESCRIPTION
				"Allows selecting the mode of GPI3 input in the RESET function"
		::= { vgp3000c01v1Entry 205 }

		-- 1.3.6.1.4.1.10106.3.101291.1.1.207
		vgp3000c01v1Gpo3RGpi4Mode OBJECT-TYPE
			SYNTAX GpiMode
			MAX-ACCESS read-write
			STATUS current
			DESCRIPTION
				"Allows selecting the mode of GPI4 input in the RESET function"
		::= { vgp3000c01v1Entry 207 }

		-- 1.3.6.1.4.1.10106.3.101291.1.1.209
		vgp3000c01v1Gpo3RGpi5Mode OBJECT-TYPE
			SYNTAX GpiMode
			MAX-ACCESS read-write
			STATUS current
			DESCRIPTION
				"Allows selecting the mode of GPI5 input in the RESET function"
		::= { vgp3000c01v1Entry 209 }

		-- 1.3.6.1.4.1.10106.3.101291.1.1.211
		vgp3000c01v1Gpo3RGpi6Mode OBJECT-TYPE
			SYNTAX GpiMode
			MAX-ACCESS read-write
			STATUS current
			DESCRIPTION
				"Allows selecting the mode of GPI6 input in the RESET function"
		::= { vgp3000c01v1Entry 211 }

		-- 1.3.6.1.4.1.10106.3.101291.1.1.213
		vgp3000c01v1Gpo3RGpi7Mode OBJECT-TYPE
			SYNTAX GpiMode
			MAX-ACCESS read-write
			STATUS current
			DESCRIPTION
				"Allows selecting the mode of GPI7 input in the RESET function"
		::= { vgp3000c01v1Entry 213 }

		-- 1.3.6.1.4.1.10106.3.101291.1.1.215
		vgp3000c01v1Gpo3RGpi8Mode OBJECT-TYPE
			SYNTAX GpiMode
			MAX-ACCESS read-write
			STATUS current
			DESCRIPTION
				"Allows selecting the mode of GPI8 input in the RESET function"
		::= { vgp3000c01v1Entry 215 }

		-- 1.3.6.1.4.1.10106.3.101291.1.1.217
		vgp3000c01v1Gpo3RDelay OBJECT-TYPE
			SYNTAX TimeX10Ms
			MAX-ACCESS read-write
			STATUS current
			DESCRIPTION
				"Allows adjusting the delay in RESET function"
		::= { vgp3000c01v1Entry 217 }

		-- 1.3.6.1.4.1.10106.3.101291.1.1.219
		vgp3000c01v1Gpo3RF OBJECT-TYPE
			SYNTAX Bit0And1Or
			MAX-ACCESS read-write
			STATUS current
			DESCRIPTION
				"Allows selecting the type of the RESET function"
		::= { vgp3000c01v1Entry 219 }

		-- 1.3.6.1.4.1.10106.3.101291.1.1.221
		vgp3000c01v1Gpo4SGpi1Ena OBJECT-TYPE
			SYNTAX Bit0No1Yes
			MAX-ACCESS read-write
			STATUS current
			DESCRIPTION
				"Enables the GPI1 input to be used in the SET function"
		::= { vgp3000c01v1Entry 221 }

		-- 1.3.6.1.4.1.10106.3.101291.1.1.223
		vgp3000c01v1Gpo4SGpi2Ena OBJECT-TYPE
			SYNTAX Bit0No1Yes
			MAX-ACCESS read-write
			STATUS current
			DESCRIPTION
				"Enables the GPI2 input to be used in the SET function"
		::= { vgp3000c01v1Entry 223 }

		-- 1.3.6.1.4.1.10106.3.101291.1.1.225
		vgp3000c01v1Gpo4SGpi3Ena OBJECT-TYPE
			SYNTAX Bit0No1Yes
			MAX-ACCESS read-write
			STATUS current
			DESCRIPTION
				"Enables the GPI3 input to be used in the SET function"
		::= { vgp3000c01v1Entry 225 }

		-- 1.3.6.1.4.1.10106.3.101291.1.1.227
		vgp3000c01v1Gpo4SGpi4Ena OBJECT-TYPE
			SYNTAX Bit0No1Yes
			MAX-ACCESS read-write
			STATUS current
			DESCRIPTION
				"Enables the GPI4 input to be used in the SET function"
		::= { vgp3000c01v1Entry 227 }

		-- 1.3.6.1.4.1.10106.3.101291.1.1.229
		vgp3000c01v1Gpo4SGpi5Ena OBJECT-TYPE
			SYNTAX Bit0No1Yes
			MAX-ACCESS read-write
			STATUS current
			DESCRIPTION
				"Enables the GPI5 input to be used in the SET function"
		::= { vgp3000c01v1Entry 229 }

		-- 1.3.6.1.4.1.10106.3.101291.1.1.231
		vgp3000c01v1Gpo4SGpi6Ena OBJECT-TYPE
			SYNTAX Bit0No1Yes
			MAX-ACCESS read-write
			STATUS current
			DESCRIPTION
				"Enables the GPI6 input to be used in the SET function"
		::= { vgp3000c01v1Entry 231 }

		-- 1.3.6.1.4.1.10106.3.101291.1.1.233
		vgp3000c01v1Gpo4SGpi7Ena OBJECT-TYPE
			SYNTAX Bit0No1Yes
			MAX-ACCESS read-write
			STATUS current
			DESCRIPTION
				"Enables the GPI7 input to be used in the SET function"
		::= { vgp3000c01v1Entry 233 }

		-- 1.3.6.1.4.1.10106.3.101291.1.1.235
		vgp3000c01v1Gpo4SGpi8Ena OBJECT-TYPE
			SYNTAX Bit0No1Yes
			MAX-ACCESS read-write
			STATUS current
			DESCRIPTION
				"Enables the GPI8 input to be used in the SET function"
		::= { vgp3000c01v1Entry 235 }

		-- 1.3.6.1.4.1.10106.3.101291.1.1.237
		vgp3000c01v1Gpo4SGpi1Mode OBJECT-TYPE
			SYNTAX GpiMode
			MAX-ACCESS read-write
			STATUS current
			DESCRIPTION
				"Allows selecting the mode of GPI1 input in the SET function"
		::= { vgp3000c01v1Entry 237 }

		-- 1.3.6.1.4.1.10106.3.101291.1.1.239
		vgp3000c01v1Gpo4SGpi2Mode OBJECT-TYPE
			SYNTAX GpiMode
			MAX-ACCESS read-write
			STATUS current
			DESCRIPTION
				"Allows selecting the mode of GPI2 input in the SET function"
		::= { vgp3000c01v1Entry 239 }

		-- 1.3.6.1.4.1.10106.3.101291.1.1.241
		vgp3000c01v1Gpo4SGpi3Mode OBJECT-TYPE
			SYNTAX GpiMode
			MAX-ACCESS read-write
			STATUS current
			DESCRIPTION
				"Allows selecting the mode of GPI3 input in the SET function"
		::= { vgp3000c01v1Entry 241 }

		-- 1.3.6.1.4.1.10106.3.101291.1.1.243
		vgp3000c01v1Gpo4SGpi4Mode OBJECT-TYPE
			SYNTAX GpiMode
			MAX-ACCESS read-write
			STATUS current
			DESCRIPTION
				"Allows selecting the mode of GPI4 input in the SET function"
		::= { vgp3000c01v1Entry 243 }

		-- 1.3.6.1.4.1.10106.3.101291.1.1.245
		vgp3000c01v1Gpo4SGpi5Mode OBJECT-TYPE
			SYNTAX GpiMode
			MAX-ACCESS read-write
			STATUS current
			DESCRIPTION
				"Allows selecting the mode of GPI5 input in the SET function"
		::= { vgp3000c01v1Entry 245 }

		-- 1.3.6.1.4.1.10106.3.101291.1.1.247
		vgp3000c01v1Gpo4SGpi6Mode OBJECT-TYPE
			SYNTAX GpiMode
			MAX-ACCESS read-write
			STATUS current
			DESCRIPTION
				"Allows selecting the mode of GPI6 input in the SET function"
		::= { vgp3000c01v1Entry 247 }

		-- 1.3.6.1.4.1.10106.3.101291.1.1.249
		vgp3000c01v1Gpo4SGpi7Mode OBJECT-TYPE
			SYNTAX GpiMode
			MAX-ACCESS read-write
			STATUS current
			DESCRIPTION
				"Allows selecting the mode of GPI7 input in the SET function"
		::= { vgp3000c01v1Entry 249 }

		-- 1.3.6.1.4.1.10106.3.101291.1.1.251
		vgp3000c01v1Gpo4SGpi8Mode OBJECT-TYPE
			SYNTAX GpiMode
			MAX-ACCESS read-write
			STATUS current
			DESCRIPTION
				"Allows selecting the mode of GPI8 input in the SET function"
		::= { vgp3000c01v1Entry 251 }

		-- 1.3.6.1.4.1.10106.3.101291.1.1.253
		vgp3000c01v1Gpo4SDelay OBJECT-TYPE
			SYNTAX TimeX10Ms
			MAX-ACCESS read-write
			STATUS current
			DESCRIPTION
				"Allows adjusting the delay in SET function"
		::= { vgp3000c01v1Entry 253 }

		-- 1.3.6.1.4.1.10106.3.101291.1.1.255
		vgp3000c01v1Gpo4SF OBJECT-TYPE
			SYNTAX Bit0And1Or
			MAX-ACCESS read-write
			STATUS current
			DESCRIPTION
				"Allows selecting the type of the SET function"
		::= { vgp3000c01v1Entry 255 }

		-- 1.3.6.1.4.1.10106.3.101291.1.1.257
		vgp3000c01v1Gpo4RGpi1Ena OBJECT-TYPE
			SYNTAX Bit0No1Yes
			MAX-ACCESS read-write
			STATUS current
			DESCRIPTION
				"Enables the GPI1 input to be used in the RESET function"
		::= { vgp3000c01v1Entry 257 }

		-- 1.3.6.1.4.1.10106.3.101291.1.1.259
		vgp3000c01v1Gpo4RGpi2Ena OBJECT-TYPE
			SYNTAX Bit0No1Yes
			MAX-ACCESS read-write
			STATUS current
			DESCRIPTION
				"Enables the GPI2 input to be used in the RESET function"
		::= { vgp3000c01v1Entry 259 }

		-- 1.3.6.1.4.1.10106.3.101291.1.1.261
		vgp3000c01v1Gpo4RGpi3Ena OBJECT-TYPE
			SYNTAX Bit0No1Yes
			MAX-ACCESS read-write
			STATUS current
			DESCRIPTION
				"Enables the GPI3 input to be used in the RESET function"
		::= { vgp3000c01v1Entry 261 }

		-- 1.3.6.1.4.1.10106.3.101291.1.1.263
		vgp3000c01v1Gpo4RGpi4Ena OBJECT-TYPE
			SYNTAX Bit0No1Yes
			MAX-ACCESS read-write
			STATUS current
			DESCRIPTION
				"Enables the GPI4 input to be used in the RESET function"
		::= { vgp3000c01v1Entry 263 }

		-- 1.3.6.1.4.1.10106.3.101291.1.1.265
		vgp3000c01v1Gpo4RGpi5Ena OBJECT-TYPE
			SYNTAX Bit0No1Yes
			MAX-ACCESS read-write
			STATUS current
			DESCRIPTION
				"Enables the GPI5 input to be used in the RESET function"
		::= { vgp3000c01v1Entry 265 }

		-- 1.3.6.1.4.1.10106.3.101291.1.1.267
		vgp3000c01v1Gpo4RGpi6Ena OBJECT-TYPE
			SYNTAX Bit0No1Yes
			MAX-ACCESS read-write
			STATUS current
			DESCRIPTION
				"Enables the GPI6 input to be used in the RESET function"
		::= { vgp3000c01v1Entry 267 }

		-- 1.3.6.1.4.1.10106.3.101291.1.1.269
		vgp3000c01v1Gpo4RGpi7Ena OBJECT-TYPE
			SYNTAX Bit0No1Yes
			MAX-ACCESS read-write
			STATUS current
			DESCRIPTION
				"Enables the GPI7 input to be used in the RESET function"
		::= { vgp3000c01v1Entry 269 }

		-- 1.3.6.1.4.1.10106.3.101291.1.1.271
		vgp3000c01v1Gpo4RGpi8Ena OBJECT-TYPE
			SYNTAX Bit0No1Yes
			MAX-ACCESS read-write
			STATUS current
			DESCRIPTION
				"Enables the GPI8 input to be used in the RESET function"
		::= { vgp3000c01v1Entry 271 }

		-- 1.3.6.1.4.1.10106.3.101291.1.1.273
		vgp3000c01v1Gpo4RGpi1Mode OBJECT-TYPE
			SYNTAX GpiMode
			MAX-ACCESS read-write
			STATUS current
			DESCRIPTION
				"Allows selecting the mode of GPI1 input in the RESET function"
		::= { vgp3000c01v1Entry 273 }

		-- 1.3.6.1.4.1.10106.3.101291.1.1.275
		vgp3000c01v1Gpo4RGpi2Mode OBJECT-TYPE
			SYNTAX GpiMode
			MAX-ACCESS read-write
			STATUS current
			DESCRIPTION
				"Allows selecting the mode of GPI2 input in the RESET function"
		::= { vgp3000c01v1Entry 275 }

		-- 1.3.6.1.4.1.10106.3.101291.1.1.277
		vgp3000c01v1Gpo4RGpi3Mode OBJECT-TYPE
			SYNTAX GpiMode
			MAX-ACCESS read-write
			STATUS current
			DESCRIPTION
				"Allows selecting the mode of GPI3 input in the RESET function"
		::= { vgp3000c01v1Entry 277 }

		-- 1.3.6.1.4.1.10106.3.101291.1.1.279
		vgp3000c01v1Gpo4RGpi4Mode OBJECT-TYPE
			SYNTAX GpiMode
			MAX-ACCESS read-write
			STATUS current
			DESCRIPTION
				"Allows selecting the mode of GPI4 input in the RESET function"
		::= { vgp3000c01v1Entry 279 }

		-- 1.3.6.1.4.1.10106.3.101291.1.1.281
		vgp3000c01v1Gpo4RGpi5Mode OBJECT-TYPE
			SYNTAX GpiMode
			MAX-ACCESS read-write
			STATUS current
			DESCRIPTION
				"Allows selecting the mode of GPI5 input in the RESET function"
		::= { vgp3000c01v1Entry 281 }

		-- 1.3.6.1.4.1.10106.3.101291.1.1.283
		vgp3000c01v1Gpo4RGpi6Mode OBJECT-TYPE
			SYNTAX GpiMode
			MAX-ACCESS read-write
			STATUS current
			DESCRIPTION
				"Allows selecting the mode of GPI6 input in the RESET function"
		::= { vgp3000c01v1Entry 283 }

		-- 1.3.6.1.4.1.10106.3.101291.1.1.285
		vgp3000c01v1Gpo4RGpi7Mode OBJECT-TYPE
			SYNTAX GpiMode
			MAX-ACCESS read-write
			STATUS current
			DESCRIPTION
				"Allows selecting the mode of GPI7 input in the RESET function"
		::= { vgp3000c01v1Entry 285 }

		-- 1.3.6.1.4.1.10106.3.101291.1.1.287
		vgp3000c01v1Gpo4RGpi8Mode OBJECT-TYPE
			SYNTAX GpiMode
			MAX-ACCESS read-write
			STATUS current
			DESCRIPTION
				"Allows selecting the mode of GPI8 input in the RESET function"
		::= { vgp3000c01v1Entry 287 }

		-- 1.3.6.1.4.1.10106.3.101291.1.1.289
		vgp3000c01v1Gpo4RDelay OBJECT-TYPE
			SYNTAX TimeX10Ms
			MAX-ACCESS read-write
			STATUS current
			DESCRIPTION
				"Allows adjusting the delay in RESET function"
		::= { vgp3000c01v1Entry 289 }

		-- 1.3.6.1.4.1.10106.3.101291.1.1.291
		vgp3000c01v1Gpo4RF OBJECT-TYPE
			SYNTAX Bit0And1Or
			MAX-ACCESS read-write
			STATUS current
			DESCRIPTION
				"Allows selecting the type of the RESET function"
		::= { vgp3000c01v1Entry 291 }

		-- 1.3.6.1.4.1.10106.3.101291.1.1.293
		vgp3000c01v1Gpo5SGpi1Ena OBJECT-TYPE
			SYNTAX Bit0No1Yes
			MAX-ACCESS read-write
			STATUS current
			DESCRIPTION
				"Enables the GPI1 input to be used in the SET function"
		::= { vgp3000c01v1Entry 293 }

		-- 1.3.6.1.4.1.10106.3.101291.1.1.295
		vgp3000c01v1Gpo5SGpi2Ena OBJECT-TYPE
			SYNTAX Bit0No1Yes
			MAX-ACCESS read-write
			STATUS current
			DESCRIPTION
				"Enables the GPI2 input to be used in the SET function"
		::= { vgp3000c01v1Entry 295 }

		-- 1.3.6.1.4.1.10106.3.101291.1.1.297
		vgp3000c01v1Gpo5SGpi3Ena OBJECT-TYPE
			SYNTAX Bit0No1Yes
			MAX-ACCESS read-write
			STATUS current
			DESCRIPTION
				"Enables the GPI3 input to be used in the SET function"
		::= { vgp3000c01v1Entry 297 }

		-- 1.3.6.1.4.1.10106.3.101291.1.1.299
		vgp3000c01v1Gpo5SGpi4Ena OBJECT-TYPE
			SYNTAX Bit0No1Yes
			MAX-ACCESS read-write
			STATUS current
			DESCRIPTION
				"Enables the GPI4 input to be used in the SET function"
		::= { vgp3000c01v1Entry 299 }

		-- 1.3.6.1.4.1.10106.3.101291.1.1.301
		vgp3000c01v1Gpo5SGpi5Ena OBJECT-TYPE
			SYNTAX Bit0No1Yes
			MAX-ACCESS read-write
			STATUS current
			DESCRIPTION
				"Enables the GPI5 input to be used in the SET function"
		::= { vgp3000c01v1Entry 301 }

		-- 1.3.6.1.4.1.10106.3.101291.1.1.303
		vgp3000c01v1Gpo5SGpi6Ena OBJECT-TYPE
			SYNTAX Bit0No1Yes
			MAX-ACCESS read-write
			STATUS current
			DESCRIPTION
				"Enables the GPI6 input to be used in the SET function"
		::= { vgp3000c01v1Entry 303 }

		-- 1.3.6.1.4.1.10106.3.101291.1.1.305
		vgp3000c01v1Gpo5SGpi7Ena OBJECT-TYPE
			SYNTAX Bit0No1Yes
			MAX-ACCESS read-write
			STATUS current
			DESCRIPTION
				"Enables the GPI7 input to be used in the SET function"
		::= { vgp3000c01v1Entry 305 }

		-- 1.3.6.1.4.1.10106.3.101291.1.1.307
		vgp3000c01v1Gpo5SGpi8Ena OBJECT-TYPE
			SYNTAX Bit0No1Yes
			MAX-ACCESS read-write
			STATUS current
			DESCRIPTION
				"Enables the GPI8 input to be used in the SET function"
		::= { vgp3000c01v1Entry 307 }

		-- 1.3.6.1.4.1.10106.3.101291.1.1.309
		vgp3000c01v1Gpo5SGpi1Mode OBJECT-TYPE
			SYNTAX GpiMode
			MAX-ACCESS read-write
			STATUS current
			DESCRIPTION
				"Allows selecting the mode of GPI1 input in the SET function"
		::= { vgp3000c01v1Entry 309 }

		-- 1.3.6.1.4.1.10106.3.101291.1.1.311
		vgp3000c01v1Gpo5SGpi2Mode OBJECT-TYPE
			SYNTAX GpiMode
			MAX-ACCESS read-write
			STATUS current
			DESCRIPTION
				"Allows selecting the mode of GPI2 input in the SET function"
		::= { vgp3000c01v1Entry 311 }

		-- 1.3.6.1.4.1.10106.3.101291.1.1.313
		vgp3000c01v1Gpo5SGpi3Mode OBJECT-TYPE
			SYNTAX GpiMode
			MAX-ACCESS read-write
			STATUS current
			DESCRIPTION
				"Allows selecting the mode of GPI3 input in the SET function"
		::= { vgp3000c01v1Entry 313 }

		-- 1.3.6.1.4.1.10106.3.101291.1.1.315
		vgp3000c01v1Gpo5SGpi4Mode OBJECT-TYPE
			SYNTAX GpiMode
			MAX-ACCESS read-write
			STATUS current
			DESCRIPTION
				"Allows selecting the mode of GPI4 input in the SET function"
		::= { vgp3000c01v1Entry 315 }

		-- 1.3.6.1.4.1.10106.3.101291.1.1.317
		vgp3000c01v1Gpo5SGpi5Mode OBJECT-TYPE
			SYNTAX GpiMode
			MAX-ACCESS read-write
			STATUS current
			DESCRIPTION
				"Allows selecting the mode of GPI5 input in the SET function"
		::= { vgp3000c01v1Entry 317 }

		-- 1.3.6.1.4.1.10106.3.101291.1.1.319
		vgp3000c01v1Gpo5SGpi6Mode OBJECT-TYPE
			SYNTAX GpiMode
			MAX-ACCESS read-write
			STATUS current
			DESCRIPTION
				"Allows selecting the mode of GPI6 input in the SET function"
		::= { vgp3000c01v1Entry 319 }

		-- 1.3.6.1.4.1.10106.3.101291.1.1.321
		vgp3000c01v1Gpo5SGpi7Mode OBJECT-TYPE
			SYNTAX GpiMode
			MAX-ACCESS read-write
			STATUS current
			DESCRIPTION
				"Allows selecting the mode of GPI7 input in the SET function"
		::= { vgp3000c01v1Entry 321 }

		-- 1.3.6.1.4.1.10106.3.101291.1.1.323
		vgp3000c01v1Gpo5SGpi8Mode OBJECT-TYPE
			SYNTAX GpiMode
			MAX-ACCESS read-write
			STATUS current
			DESCRIPTION
				"Allows selecting the mode of GPI8 input in the SET function"
		::= { vgp3000c01v1Entry 323 }

		-- 1.3.6.1.4.1.10106.3.101291.1.1.325
		vgp3000c01v1Gpo5SDelay OBJECT-TYPE
			SYNTAX TimeX10Ms
			MAX-ACCESS read-write
			STATUS current
			DESCRIPTION
				"Allows adjusting the delay in SET function"
		::= { vgp3000c01v1Entry 325 }

		-- 1.3.6.1.4.1.10106.3.101291.1.1.327
		vgp3000c01v1Gpo5SF OBJECT-TYPE
			SYNTAX Bit0And1Or
			MAX-ACCESS read-write
			STATUS current
			DESCRIPTION
				"Allows selecting the type of the SET function"
		::= { vgp3000c01v1Entry 327 }

		-- 1.3.6.1.4.1.10106.3.101291.1.1.329
		vgp3000c01v1Gpo5RGpi1Ena OBJECT-TYPE
			SYNTAX Bit0No1Yes
			MAX-ACCESS read-write
			STATUS current
			DESCRIPTION
				"Enables the GPI1 input to be used in the RESET function"
		::= { vgp3000c01v1Entry 329 }

		-- 1.3.6.1.4.1.10106.3.101291.1.1.331
		vgp3000c01v1Gpo5RGpi2Ena OBJECT-TYPE
			SYNTAX Bit0No1Yes
			MAX-ACCESS read-write
			STATUS current
			DESCRIPTION
				"Enables the GPI2 input to be used in the RESET function"
		::= { vgp3000c01v1Entry 331 }

		-- 1.3.6.1.4.1.10106.3.101291.1.1.333
		vgp3000c01v1Gpo5RGpi3Ena OBJECT-TYPE
			SYNTAX Bit0No1Yes
			MAX-ACCESS read-write
			STATUS current
			DESCRIPTION
				"Enables the GPI3 input to be used in the RESET function"
		::= { vgp3000c01v1Entry 333 }

		-- 1.3.6.1.4.1.10106.3.101291.1.1.335
		vgp3000c01v1Gpo5RGpi4Ena OBJECT-TYPE
			SYNTAX Bit0No1Yes
			MAX-ACCESS read-write
			STATUS current
			DESCRIPTION
				"Enables the GPI4 input to be used in the RESET function"
		::= { vgp3000c01v1Entry 335 }

		-- 1.3.6.1.4.1.10106.3.101291.1.1.337
		vgp3000c01v1Gpo5RGpi5Ena OBJECT-TYPE
			SYNTAX Bit0No1Yes
			MAX-ACCESS read-write
			STATUS current
			DESCRIPTION
				"Enables the GPI5 input to be used in the RESET function"
		::= { vgp3000c01v1Entry 337 }

		-- 1.3.6.1.4.1.10106.3.101291.1.1.339
		vgp3000c01v1Gpo5RGpi6Ena OBJECT-TYPE
			SYNTAX Bit0No1Yes
			MAX-ACCESS read-write
			STATUS current
			DESCRIPTION
				"Enables the GPI6 input to be used in the RESET function"
		::= { vgp3000c01v1Entry 339 }

		-- 1.3.6.1.4.1.10106.3.101291.1.1.341
		vgp3000c01v1Gpo5RGpi7Ena OBJECT-TYPE
			SYNTAX Bit0No1Yes
			MAX-ACCESS read-write
			STATUS current
			DESCRIPTION
				"Enables the GPI7 input to be used in the RESET function"
		::= { vgp3000c01v1Entry 341 }

		-- 1.3.6.1.4.1.10106.3.101291.1.1.343
		vgp3000c01v1Gpo5RGpi8Ena OBJECT-TYPE
			SYNTAX Bit0No1Yes
			MAX-ACCESS read-write
			STATUS current
			DESCRIPTION
				"Enables the GPI8 input to be used in the RESET function"
		::= { vgp3000c01v1Entry 343 }

		-- 1.3.6.1.4.1.10106.3.101291.1.1.345
		vgp3000c01v1Gpo5RGpi1Mode OBJECT-TYPE
			SYNTAX GpiMode
			MAX-ACCESS read-write
			STATUS current
			DESCRIPTION
				"Allows selecting the mode of GPI1 input in the RESET function"
		::= { vgp3000c01v1Entry 345 }

		-- 1.3.6.1.4.1.10106.3.101291.1.1.347
		vgp3000c01v1Gpo5RGpi2Mode OBJECT-TYPE
			SYNTAX GpiMode
			MAX-ACCESS read-write
			STATUS current
			DESCRIPTION
				"Allows selecting the mode of GPI2 input in the RESET function"
		::= { vgp3000c01v1Entry 347 }

		-- 1.3.6.1.4.1.10106.3.101291.1.1.349
		vgp3000c01v1Gpo5RGpi3Mode OBJECT-TYPE
			SYNTAX GpiMode
			MAX-ACCESS read-write
			STATUS current
			DESCRIPTION
				"Allows selecting the mode of GPI3 input in the RESET function"
		::= { vgp3000c01v1Entry 349 }

		-- 1.3.6.1.4.1.10106.3.101291.1.1.351
		vgp3000c01v1Gpo5RGpi4Mode OBJECT-TYPE
			SYNTAX GpiMode
			MAX-ACCESS read-write
			STATUS current
			DESCRIPTION
				"Allows selecting the mode of GPI4 input in the RESET function"
		::= { vgp3000c01v1Entry 351 }

		-- 1.3.6.1.4.1.10106.3.101291.1.1.353
		vgp3000c01v1Gpo5RGpi5Mode OBJECT-TYPE
			SYNTAX GpiMode
			MAX-ACCESS read-write
			STATUS current
			DESCRIPTION
				"Allows selecting the mode of GPI5 input in the RESET function"
		::= { vgp3000c01v1Entry 353 }

		-- 1.3.6.1.4.1.10106.3.101291.1.1.355
		vgp3000c01v1Gpo5RGpi6Mode OBJECT-TYPE
			SYNTAX GpiMode
			MAX-ACCESS read-write
			STATUS current
			DESCRIPTION
				"Allows selecting the mode of GPI6 input in the RESET function"
		::= { vgp3000c01v1Entry 355 }

		-- 1.3.6.1.4.1.10106.3.101291.1.1.357
		vgp3000c01v1Gpo5RGpi7Mode OBJECT-TYPE
			SYNTAX GpiMode
			MAX-ACCESS read-write
			STATUS current
			DESCRIPTION
				"Allows selecting the mode of GPI7 input in the RESET function"
		::= { vgp3000c01v1Entry 357 }

		-- 1.3.6.1.4.1.10106.3.101291.1.1.359
		vgp3000c01v1Gpo5RGpi8Mode OBJECT-TYPE
			SYNTAX GpiMode
			MAX-ACCESS read-write
			STATUS current
			DESCRIPTION
				"Allows selecting the mode of GPI8 input in the RESET function"
		::= { vgp3000c01v1Entry 359 }

		-- 1.3.6.1.4.1.10106.3.101291.1.1.361
		vgp3000c01v1Gpo5RDelay OBJECT-TYPE
			SYNTAX TimeX10Ms
			MAX-ACCESS read-write
			STATUS current
			DESCRIPTION
				"Allows adjusting the delay in RESET function"
		::= { vgp3000c01v1Entry 361 }

		-- 1.3.6.1.4.1.10106.3.101291.1.1.363
		vgp3000c01v1Gpo5RF OBJECT-TYPE
			SYNTAX Bit0And1Or
			MAX-ACCESS read-write
			STATUS current
			DESCRIPTION
				"Allows selecting the type of the RESET function"
		::= { vgp3000c01v1Entry 363 }

		-- 1.3.6.1.4.1.10106.3.101291.1.1.365
		vgp3000c01v1Gpo6SGpi1Ena OBJECT-TYPE
			SYNTAX Bit0No1Yes
			MAX-ACCESS read-write
			STATUS current
			DESCRIPTION
				"Enables the GPI1 input to be used in the SET function"
		::= { vgp3000c01v1Entry 365 }

		-- 1.3.6.1.4.1.10106.3.101291.1.1.367
		vgp3000c01v1Gpo6SGpi2Ena OBJECT-TYPE
			SYNTAX Bit0No1Yes
			MAX-ACCESS read-write
			STATUS current
			DESCRIPTION
				"Enables the GPI2 input to be used in the SET function"
		::= { vgp3000c01v1Entry 367 }

		-- 1.3.6.1.4.1.10106.3.101291.1.1.369
		vgp3000c01v1Gpo6SGpi3Ena OBJECT-TYPE
			SYNTAX Bit0No1Yes
			MAX-ACCESS read-write
			STATUS current
			DESCRIPTION
				"Enables the GPI3 input to be used in the SET function"
		::= { vgp3000c01v1Entry 369 }

		-- 1.3.6.1.4.1.10106.3.101291.1.1.371
		vgp3000c01v1Gpo6SGpi4Ena OBJECT-TYPE
			SYNTAX Bit0No1Yes
			MAX-ACCESS read-write
			STATUS current
			DESCRIPTION
				"Enables the GPI4 input to be used in the SET function"
		::= { vgp3000c01v1Entry 371 }

		-- 1.3.6.1.4.1.10106.3.101291.1.1.373
		vgp3000c01v1Gpo6SGpi5Ena OBJECT-TYPE
			SYNTAX Bit0No1Yes
			MAX-ACCESS read-write
			STATUS current
			DESCRIPTION
				"Enables the GPI5 input to be used in the SET function"
		::= { vgp3000c01v1Entry 373 }

		-- 1.3.6.1.4.1.10106.3.101291.1.1.375
		vgp3000c01v1Gpo6SGpi6Ena OBJECT-TYPE
			SYNTAX Bit0No1Yes
			MAX-ACCESS read-write
			STATUS current
			DESCRIPTION
				"Enables the GPI6 input to be used in the SET function"
		::= { vgp3000c01v1Entry 375 }

		-- 1.3.6.1.4.1.10106.3.101291.1.1.377
		vgp3000c01v1Gpo6SGpi7Ena OBJECT-TYPE
			SYNTAX Bit0No1Yes
			MAX-ACCESS read-write
			STATUS current
			DESCRIPTION
				"Enables the GPI7 input to be used in the SET function"
		::= { vgp3000c01v1Entry 377 }

		-- 1.3.6.1.4.1.10106.3.101291.1.1.379
		vgp3000c01v1Gpo6SGpi8Ena OBJECT-TYPE
			SYNTAX Bit0No1Yes
			MAX-ACCESS read-write
			STATUS current
			DESCRIPTION
				"Enables the GPI8 input to be used in the SET function"
		::= { vgp3000c01v1Entry 379 }

		-- 1.3.6.1.4.1.10106.3.101291.1.1.381
		vgp3000c01v1Gpo6SGpi1Mode OBJECT-TYPE
			SYNTAX GpiMode
			MAX-ACCESS read-write
			STATUS current
			DESCRIPTION
				"Allows selecting the mode of GPI1 input in the SET function"
		::= { vgp3000c01v1Entry 381 }

		-- 1.3.6.1.4.1.10106.3.101291.1.1.383
		vgp3000c01v1Gpo6SGpi2Mode OBJECT-TYPE
			SYNTAX GpiMode
			MAX-ACCESS read-write
			STATUS current
			DESCRIPTION
				"Allows selecting the mode of GPI2 input in the SET function"
		::= { vgp3000c01v1Entry 383 }

		-- 1.3.6.1.4.1.10106.3.101291.1.1.385
		vgp3000c01v1Gpo6SGpi3Mode OBJECT-TYPE
			SYNTAX GpiMode
			MAX-ACCESS read-write
			STATUS current
			DESCRIPTION
				"Allows selecting the mode of GPI3 input in the SET function"
		::= { vgp3000c01v1Entry 385 }

		-- 1.3.6.1.4.1.10106.3.101291.1.1.387
		vgp3000c01v1Gpo6SGpi4Mode OBJECT-TYPE
			SYNTAX GpiMode
			MAX-ACCESS read-write
			STATUS current
			DESCRIPTION
				"Allows selecting the mode of GPI4 input in the SET function"
		::= { vgp3000c01v1Entry 387 }

		-- 1.3.6.1.4.1.10106.3.101291.1.1.389
		vgp3000c01v1Gpo6SGpi5Mode OBJECT-TYPE
			SYNTAX GpiMode
			MAX-ACCESS read-write
			STATUS current
			DESCRIPTION
				"Allows selecting the mode of GPI5 input in the SET function"
		::= { vgp3000c01v1Entry 389 }

		-- 1.3.6.1.4.1.10106.3.101291.1.1.391
		vgp3000c01v1Gpo6SGpi6Mode OBJECT-TYPE
			SYNTAX GpiMode
			MAX-ACCESS read-write
			STATUS current
			DESCRIPTION
				"Allows selecting the mode of GPI6 input in the SET function"
		::= { vgp3000c01v1Entry 391 }

		-- 1.3.6.1.4.1.10106.3.101291.1.1.393
		vgp3000c01v1Gpo6SGpi7Mode OBJECT-TYPE
			SYNTAX GpiMode
			MAX-ACCESS read-write
			STATUS current
			DESCRIPTION
				"Allows selecting the mode of GPI7 input in the SET function"
		::= { vgp3000c01v1Entry 393 }

		-- 1.3.6.1.4.1.10106.3.101291.1.1.395
		vgp3000c01v1Gpo6SGpi8Mode OBJECT-TYPE
			SYNTAX GpiMode
			MAX-ACCESS read-write
			STATUS current
			DESCRIPTION
				"Allows selecting the mode of GPI8 input in the SET function"
		::= { vgp3000c01v1Entry 395 }

		-- 1.3.6.1.4.1.10106.3.101291.1.1.397
		vgp3000c01v1Gpo6SDelay OBJECT-TYPE
			SYNTAX TimeX10Ms
			MAX-ACCESS read-write
			STATUS current
			DESCRIPTION
				"Allows adjusting the delay in SET function"
		::= { vgp3000c01v1Entry 397 }

		-- 1.3.6.1.4.1.10106.3.101291.1.1.399
		vgp3000c01v1Gpo6SF OBJECT-TYPE
			SYNTAX Bit0And1Or
			MAX-ACCESS read-write
			STATUS current
			DESCRIPTION
				"Allows selecting the type of the SET function"
		::= { vgp3000c01v1Entry 399 }

		-- 1.3.6.1.4.1.10106.3.101291.1.1.401
		vgp3000c01v1Gpo6RGpi1Ena OBJECT-TYPE
			SYNTAX Bit0No1Yes
			MAX-ACCESS read-write
			STATUS current
			DESCRIPTION
				"Enables the GPI1 input to be used in the RESET function"
		::= { vgp3000c01v1Entry 401 }

		-- 1.3.6.1.4.1.10106.3.101291.1.1.403
		vgp3000c01v1Gpo6RGpi2Ena OBJECT-TYPE
			SYNTAX Bit0No1Yes
			MAX-ACCESS read-write
			STATUS current
			DESCRIPTION
				"Enables the GPI2 input to be used in the RESET function"
		::= { vgp3000c01v1Entry 403 }

		-- 1.3.6.1.4.1.10106.3.101291.1.1.405
		vgp3000c01v1Gpo6RGpi3Ena OBJECT-TYPE
			SYNTAX Bit0No1Yes
			MAX-ACCESS read-write
			STATUS current
			DESCRIPTION
				"Enables the GPI3 input to be used in the RESET function"
		::= { vgp3000c01v1Entry 405 }

		-- 1.3.6.1.4.1.10106.3.101291.1.1.407
		vgp3000c01v1Gpo6RGpi4Ena OBJECT-TYPE
			SYNTAX Bit0No1Yes
			MAX-ACCESS read-write
			STATUS current
			DESCRIPTION
				"Enables the GPI4 input to be used in the RESET function"
		::= { vgp3000c01v1Entry 407 }

		-- 1.3.6.1.4.1.10106.3.101291.1.1.409
		vgp3000c01v1Gpo6RGpi5Ena OBJECT-TYPE
			SYNTAX Bit0No1Yes
			MAX-ACCESS read-write
			STATUS current
			DESCRIPTION
				"Enables the GPI5 input to be used in the RESET function"
		::= { vgp3000c01v1Entry 409 }

		-- 1.3.6.1.4.1.10106.3.101291.1.1.411
		vgp3000c01v1Gpo6RGpi6Ena OBJECT-TYPE
			SYNTAX Bit0No1Yes
			MAX-ACCESS read-write
			STATUS current
			DESCRIPTION
				"Enables the GPI6 input to be used in the RESET function"
		::= { vgp3000c01v1Entry 411 }

		-- 1.3.6.1.4.1.10106.3.101291.1.1.413
		vgp3000c01v1Gpo6RGpi7Ena OBJECT-TYPE
			SYNTAX Bit0No1Yes
			MAX-ACCESS read-write
			STATUS current
			DESCRIPTION
				"Enables the GPI7 input to be used in the RESET function"
		::= { vgp3000c01v1Entry 413 }

		-- 1.3.6.1.4.1.10106.3.101291.1.1.415
		vgp3000c01v1Gpo6RGpi8Ena OBJECT-TYPE
			SYNTAX Bit0No1Yes
			MAX-ACCESS read-write
			STATUS current
			DESCRIPTION
				"Enables the GPI8 input to be used in the RESET function"
		::= { vgp3000c01v1Entry 415 }

		-- 1.3.6.1.4.1.10106.3.101291.1.1.417
		vgp3000c01v1Gpo6RGpi1Mode OBJECT-TYPE
			SYNTAX GpiMode
			MAX-ACCESS read-write
			STATUS current
			DESCRIPTION
				"Allows selecting the mode of GPI1 input in the RESET function"
		::= { vgp3000c01v1Entry 417 }

		-- 1.3.6.1.4.1.10106.3.101291.1.1.419
		vgp3000c01v1Gpo6RGpi2Mode OBJECT-TYPE
			SYNTAX GpiMode
			MAX-ACCESS read-write
			STATUS current
			DESCRIPTION
				"Allows selecting the mode of GPI2 input in the RESET function"
		::= { vgp3000c01v1Entry 419 }

		-- 1.3.6.1.4.1.10106.3.101291.1.1.421
		vgp3000c01v1Gpo6RGpi3Mode OBJECT-TYPE
			SYNTAX GpiMode
			MAX-ACCESS read-write
			STATUS current
			DESCRIPTION
				"Allows selecting the mode of GPI3 input in the RESET function"
		::= { vgp3000c01v1Entry 421 }

		-- 1.3.6.1.4.1.10106.3.101291.1.1.423
		vgp3000c01v1Gpo6RGpi4Mode OBJECT-TYPE
			SYNTAX GpiMode
			MAX-ACCESS read-write
			STATUS current
			DESCRIPTION
				"Allows selecting the mode of GPI4 input in the RESET function"
		::= { vgp3000c01v1Entry 423 }

		-- 1.3.6.1.4.1.10106.3.101291.1.1.425
		vgp3000c01v1Gpo6RGpi5Mode OBJECT-TYPE
			SYNTAX GpiMode
			MAX-ACCESS read-write
			STATUS current
			DESCRIPTION
				"Allows selecting the mode of GPI5 input in the RESET function"
		::= { vgp3000c01v1Entry 425 }

		-- 1.3.6.1.4.1.10106.3.101291.1.1.427
		vgp3000c01v1Gpo6RGpi6Mode OBJECT-TYPE
			SYNTAX GpiMode
			MAX-ACCESS read-write
			STATUS current
			DESCRIPTION
				"Allows selecting the mode of GPI6 input in the RESET function"
		::= { vgp3000c01v1Entry 427 }

		-- 1.3.6.1.4.1.10106.3.101291.1.1.429
		vgp3000c01v1Gpo6RGpi7Mode OBJECT-TYPE
			SYNTAX GpiMode
			MAX-ACCESS read-write
			STATUS current
			DESCRIPTION
				"Allows selecting the mode of GPI7 input in the RESET function"
		::= { vgp3000c01v1Entry 429 }

		-- 1.3.6.1.4.1.10106.3.101291.1.1.431
		vgp3000c01v1Gpo6RGpi8Mode OBJECT-TYPE
			SYNTAX GpiMode
			MAX-ACCESS read-write
			STATUS current
			DESCRIPTION
				"Allows selecting the mode of GPI8 input in the RESET function"
		::= { vgp3000c01v1Entry 431 }

		-- 1.3.6.1.4.1.10106.3.101291.1.1.433
		vgp3000c01v1Gpo6RDelay OBJECT-TYPE
			SYNTAX TimeX10Ms
			MAX-ACCESS read-write
			STATUS current
			DESCRIPTION
				"Allows adjusting the delay in RESET function"
		::= { vgp3000c01v1Entry 433 }

		-- 1.3.6.1.4.1.10106.3.101291.1.1.435
		vgp3000c01v1Gpo6RF OBJECT-TYPE
			SYNTAX Bit0And1Or
			MAX-ACCESS read-write
			STATUS current
			DESCRIPTION
				"Allows selecting the type of the RESET function"
		::= { vgp3000c01v1Entry 435 }

		-- 1.3.6.1.4.1.10106.3.101291.1.1.437
		vgp3000c01v1Gpo7SGpi1Ena OBJECT-TYPE
			SYNTAX Bit0No1Yes
			MAX-ACCESS read-write
			STATUS current
			DESCRIPTION
				"Enables the GPI1 input to be used in the SET function"
		::= { vgp3000c01v1Entry 437 }

		-- 1.3.6.1.4.1.10106.3.101291.1.1.439
		vgp3000c01v1Gpo7SGpi2Ena OBJECT-TYPE
			SYNTAX Bit0No1Yes
			MAX-ACCESS read-write
			STATUS current
			DESCRIPTION
				"Enables the GPI2 input to be used in the SET function"
		::= { vgp3000c01v1Entry 439 }

		-- 1.3.6.1.4.1.10106.3.101291.1.1.441
		vgp3000c01v1Gpo7SGpi3Ena OBJECT-TYPE
			SYNTAX Bit0No1Yes
			MAX-ACCESS read-write
			STATUS current
			DESCRIPTION
				"Enables the GPI3 input to be used in the SET function"
		::= { vgp3000c01v1Entry 441 }

		-- 1.3.6.1.4.1.10106.3.101291.1.1.443
		vgp3000c01v1Gpo7SGpi4Ena OBJECT-TYPE
			SYNTAX Bit0No1Yes
			MAX-ACCESS read-write
			STATUS current
			DESCRIPTION
				"Enables the GPI4 input to be used in the SET function"
		::= { vgp3000c01v1Entry 443 }

		-- 1.3.6.1.4.1.10106.3.101291.1.1.445
		vgp3000c01v1Gpo7SGpi5Ena OBJECT-TYPE
			SYNTAX Bit0No1Yes
			MAX-ACCESS read-write
			STATUS current
			DESCRIPTION
				"Enables the GPI5 input to be used in the SET function"
		::= { vgp3000c01v1Entry 445 }

		-- 1.3.6.1.4.1.10106.3.101291.1.1.447
		vgp3000c01v1Gpo7SGpi6Ena OBJECT-TYPE
			SYNTAX Bit0No1Yes
			MAX-ACCESS read-write
			STATUS current
			DESCRIPTION
				"Enables the GPI6 input to be used in the SET function"
		::= { vgp3000c01v1Entry 447 }

		-- 1.3.6.1.4.1.10106.3.101291.1.1.449
		vgp3000c01v1Gpo7SGpi7Ena OBJECT-TYPE
			SYNTAX Bit0No1Yes
			MAX-ACCESS read-write
			STATUS current
			DESCRIPTION
				"Enables the GPI7 input to be used in the SET function"
		::= { vgp3000c01v1Entry 449 }

		-- 1.3.6.1.4.1.10106.3.101291.1.1.451
		vgp3000c01v1Gpo7SGpi8Ena OBJECT-TYPE
			SYNTAX Bit0No1Yes
			MAX-ACCESS read-write
			STATUS current
			DESCRIPTION
				"Enables the GPI8 input to be used in the SET function"
		::= { vgp3000c01v1Entry 451 }

		-- 1.3.6.1.4.1.10106.3.101291.1.1.453
		vgp3000c01v1Gpo7SGpi1Mode OBJECT-TYPE
			SYNTAX GpiMode
			MAX-ACCESS read-write
			STATUS current
			DESCRIPTION
				"Allows selecting the mode of GPI1 input in the SET function"
		::= { vgp3000c01v1Entry 453 }

		-- 1.3.6.1.4.1.10106.3.101291.1.1.455
		vgp3000c01v1Gpo7SGpi2Mode OBJECT-TYPE
			SYNTAX GpiMode
			MAX-ACCESS read-write
			STATUS current
			DESCRIPTION
				"Allows selecting the mode of GPI2 input in the SET function"
		::= { vgp3000c01v1Entry 455 }

		-- 1.3.6.1.4.1.10106.3.101291.1.1.457
		vgp3000c01v1Gpo7SGpi3Mode OBJECT-TYPE
			SYNTAX GpiMode
			MAX-ACCESS read-write
			STATUS current
			DESCRIPTION
				"Allows selecting the mode of GPI3 input in the SET function"
		::= { vgp3000c01v1Entry 457 }

		-- 1.3.6.1.4.1.10106.3.101291.1.1.459
		vgp3000c01v1Gpo7SGpi4Mode OBJECT-TYPE
			SYNTAX GpiMode
			MAX-ACCESS read-write
			STATUS current
			DESCRIPTION
				"Allows selecting the mode of GPI4 input in the SET function"
		::= { vgp3000c01v1Entry 459 }

		-- 1.3.6.1.4.1.10106.3.101291.1.1.461
		vgp3000c01v1Gpo7SGpi5Mode OBJECT-TYPE
			SYNTAX GpiMode
			MAX-ACCESS read-write
			STATUS current
			DESCRIPTION
				"Allows selecting the mode of GPI5 input in the SET function"
		::= { vgp3000c01v1Entry 461 }

		-- 1.3.6.1.4.1.10106.3.101291.1.1.463
		vgp3000c01v1Gpo7SGpi6Mode OBJECT-TYPE
			SYNTAX GpiMode
			MAX-ACCESS read-write
			STATUS current
			DESCRIPTION
				"Allows selecting the mode of GPI6 input in the SET function"
		::= { vgp3000c01v1Entry 463 }

		-- 1.3.6.1.4.1.10106.3.101291.1.1.465
		vgp3000c01v1Gpo7SGpi7Mode OBJECT-TYPE
			SYNTAX GpiMode
			MAX-ACCESS read-write
			STATUS current
			DESCRIPTION
				"Allows selecting the mode of GPI7 input in the SET function"
		::= { vgp3000c01v1Entry 465 }

		-- 1.3.6.1.4.1.10106.3.101291.1.1.467
		vgp3000c01v1Gpo7SGpi8Mode OBJECT-TYPE
			SYNTAX GpiMode
			MAX-ACCESS read-write
			STATUS current
			DESCRIPTION
				"Allows selecting the mode of GPI8 input in the SET function"
		::= { vgp3000c01v1Entry 467 }

		-- 1.3.6.1.4.1.10106.3.101291.1.1.469
		vgp3000c01v1Gpo7SDelay OBJECT-TYPE
			SYNTAX TimeX10Ms
			MAX-ACCESS read-write
			STATUS current
			DESCRIPTION
				"Allows adjusting the delay in SET function"
		::= { vgp3000c01v1Entry 469 }

		-- 1.3.6.1.4.1.10106.3.101291.1.1.471
		vgp3000c01v1Gpo7SF OBJECT-TYPE
			SYNTAX Bit0And1Or
			MAX-ACCESS read-write
			STATUS current
			DESCRIPTION
				"Allows selecting the type of the SET function"
		::= { vgp3000c01v1Entry 471 }

		-- 1.3.6.1.4.1.10106.3.101291.1.1.473
		vgp3000c01v1Gpo7RGpi1Ena OBJECT-TYPE
			SYNTAX Bit0No1Yes
			MAX-ACCESS read-write
			STATUS current
			DESCRIPTION
				"Enables the GPI1 input to be used in the RESET function"
		::= { vgp3000c01v1Entry 473 }

		-- 1.3.6.1.4.1.10106.3.101291.1.1.475
		vgp3000c01v1Gpo7RGpi2Ena OBJECT-TYPE
			SYNTAX Bit0No1Yes
			MAX-ACCESS read-write
			STATUS current
			DESCRIPTION
				"Enables the GPI2 input to be used in the RESET function"
		::= { vgp3000c01v1Entry 475 }

		-- 1.3.6.1.4.1.10106.3.101291.1.1.477
		vgp3000c01v1Gpo7RGpi3Ena OBJECT-TYPE
			SYNTAX Bit0No1Yes
			MAX-ACCESS read-write
			STATUS current
			DESCRIPTION
				"Enables the GPI3 input to be used in the RESET function"
		::= { vgp3000c01v1Entry 477 }

		-- 1.3.6.1.4.1.10106.3.101291.1.1.479
		vgp3000c01v1Gpo7RGpi4Ena OBJECT-TYPE
			SYNTAX Bit0No1Yes
			MAX-ACCESS read-write
			STATUS current
			DESCRIPTION
				"Enables the GPI4 input to be used in the RESET function"
		::= { vgp3000c01v1Entry 479 }

		-- 1.3.6.1.4.1.10106.3.101291.1.1.481
		vgp3000c01v1Gpo7RGpi5Ena OBJECT-TYPE
			SYNTAX Bit0No1Yes
			MAX-ACCESS read-write
			STATUS current
			DESCRIPTION
				"Enables the GPI5 input to be used in the RESET function"
		::= { vgp3000c01v1Entry 481 }

		-- 1.3.6.1.4.1.10106.3.101291.1.1.483
		vgp3000c01v1Gpo7RGpi6Ena OBJECT-TYPE
			SYNTAX Bit0No1Yes
			MAX-ACCESS read-write
			STATUS current
			DESCRIPTION
				"Enables the GPI6 input to be used in the RESET function"
		::= { vgp3000c01v1Entry 483 }

		-- 1.3.6.1.4.1.10106.3.101291.1.1.485
		vgp3000c01v1Gpo7RGpi7Ena OBJECT-TYPE
			SYNTAX Bit0No1Yes
			MAX-ACCESS read-write
			STATUS current
			DESCRIPTION
				"Enables the GPI7 input to be used in the RESET function"
		::= { vgp3000c01v1Entry 485 }

		-- 1.3.6.1.4.1.10106.3.101291.1.1.487
		vgp3000c01v1Gpo7RGpi8Ena OBJECT-TYPE
			SYNTAX Bit0No1Yes
			MAX-ACCESS read-write
			STATUS current
			DESCRIPTION
				"Enables the GPI8 input to be used in the RESET function"
		::= { vgp3000c01v1Entry 487 }

		-- 1.3.6.1.4.1.10106.3.101291.1.1.489
		vgp3000c01v1Gpo7RGpi1Mode OBJECT-TYPE
			SYNTAX GpiMode
			MAX-ACCESS read-write
			STATUS current
			DESCRIPTION
				"Allows selecting the mode of GPI1 input in the RESET function"
		::= { vgp3000c01v1Entry 489 }

		-- 1.3.6.1.4.1.10106.3.101291.1.1.491
		vgp3000c01v1Gpo7RGpi2Mode OBJECT-TYPE
			SYNTAX GpiMode
			MAX-ACCESS read-write
			STATUS current
			DESCRIPTION
				"Allows selecting the mode of GPI2 input in the RESET function"
		::= { vgp3000c01v1Entry 491 }

		-- 1.3.6.1.4.1.10106.3.101291.1.1.493
		vgp3000c01v1Gpo7RGpi3Mode OBJECT-TYPE
			SYNTAX GpiMode
			MAX-ACCESS read-write
			STATUS current
			DESCRIPTION
				"Allows selecting the mode of GPI3 input in the RESET function"
		::= { vgp3000c01v1Entry 493 }

		-- 1.3.6.1.4.1.10106.3.101291.1.1.495
		vgp3000c01v1Gpo7RGpi4Mode OBJECT-TYPE
			SYNTAX GpiMode
			MAX-ACCESS read-write
			STATUS current
			DESCRIPTION
				"Allows selecting the mode of GPI4 input in the RESET function"
		::= { vgp3000c01v1Entry 495 }

		-- 1.3.6.1.4.1.10106.3.101291.1.1.497
		vgp3000c01v1Gpo7RGpi5Mode OBJECT-TYPE
			SYNTAX GpiMode
			MAX-ACCESS read-write
			STATUS current
			DESCRIPTION
				"Allows selecting the mode of GPI5 input in the RESET function"
		::= { vgp3000c01v1Entry 497 }

		-- 1.3.6.1.4.1.10106.3.101291.1.1.499
		vgp3000c01v1Gpo7RGpi6Mode OBJECT-TYPE
			SYNTAX GpiMode
			MAX-ACCESS read-write
			STATUS current
			DESCRIPTION
				"Allows selecting the mode of GPI6 input in the RESET function"
		::= { vgp3000c01v1Entry 499 }

		-- 1.3.6.1.4.1.10106.3.101291.1.1.501
		vgp3000c01v1Gpo7RGpi7Mode OBJECT-TYPE
			SYNTAX GpiMode
			MAX-ACCESS read-write
			STATUS current
			DESCRIPTION
				"Allows selecting the mode of GPI7 input in the RESET function"
		::= { vgp3000c01v1Entry 501 }

		-- 1.3.6.1.4.1.10106.3.101291.1.1.503
		vgp3000c01v1Gpo7RGpi8Mode OBJECT-TYPE
			SYNTAX GpiMode
			MAX-ACCESS read-write
			STATUS current
			DESCRIPTION
				"Allows selecting the mode of GPI8 input in the RESET function"
		::= { vgp3000c01v1Entry 503 }

		-- 1.3.6.1.4.1.10106.3.101291.1.1.505
		vgp3000c01v1Gpo7RDelay OBJECT-TYPE
			SYNTAX TimeX10Ms
			MAX-ACCESS read-write
			STATUS current
			DESCRIPTION
				"Allows adjusting the delay in RESET function"
		::= { vgp3000c01v1Entry 505 }

		-- 1.3.6.1.4.1.10106.3.101291.1.1.507
		vgp3000c01v1Gpo7RF OBJECT-TYPE
			SYNTAX Bit0And1Or
			MAX-ACCESS read-write
			STATUS current
			DESCRIPTION
				"Allows selecting the type of the RESET function"
		::= { vgp3000c01v1Entry 507 }

		-- 1.3.6.1.4.1.10106.3.101291.1.1.509
		vgp3000c01v1Gpo8SGpi1Ena OBJECT-TYPE
			SYNTAX Bit0No1Yes
			MAX-ACCESS read-write
			STATUS current
			DESCRIPTION
				"Enables the GPI1 input to be used in the SET function"
		::= { vgp3000c01v1Entry 509 }

		-- 1.3.6.1.4.1.10106.3.101291.1.1.511
		vgp3000c01v1Gpo8SGpi2Ena OBJECT-TYPE
			SYNTAX Bit0No1Yes
			MAX-ACCESS read-write
			STATUS current
			DESCRIPTION
				"Enables the GPI2 input to be used in the SET function"
		::= { vgp3000c01v1Entry 511 }

		-- 1.3.6.1.4.1.10106.3.101291.1.1.513
		vgp3000c01v1Gpo8SGpi3Ena OBJECT-TYPE
			SYNTAX Bit0No1Yes
			MAX-ACCESS read-write
			STATUS current
			DESCRIPTION
				"Enables the GPI3 input to be used in the SET function"
		::= { vgp3000c01v1Entry 513 }

		-- 1.3.6.1.4.1.10106.3.101291.1.1.515
		vgp3000c01v1Gpo8SGpi4Ena OBJECT-TYPE
			SYNTAX Bit0No1Yes
			MAX-ACCESS read-write
			STATUS current
			DESCRIPTION
				"Enables the GPI4 input to be used in the SET function"
		::= { vgp3000c01v1Entry 515 }

		-- 1.3.6.1.4.1.10106.3.101291.1.1.517
		vgp3000c01v1Gpo8SGpi5Ena OBJECT-TYPE
			SYNTAX Bit0No1Yes
			MAX-ACCESS read-write
			STATUS current
			DESCRIPTION
				"Enables the GPI5 input to be used in the SET function"
		::= { vgp3000c01v1Entry 517 }

		-- 1.3.6.1.4.1.10106.3.101291.1.1.519
		vgp3000c01v1Gpo8SGpi6Ena OBJECT-TYPE
			SYNTAX Bit0No1Yes
			MAX-ACCESS read-write
			STATUS current
			DESCRIPTION
				"Enables the GPI6 input to be used in the SET function"
		::= { vgp3000c01v1Entry 519 }

		-- 1.3.6.1.4.1.10106.3.101291.1.1.521
		vgp3000c01v1Gpo8SGpi7Ena OBJECT-TYPE
			SYNTAX Bit0No1Yes
			MAX-ACCESS read-write
			STATUS current
			DESCRIPTION
				"Enables the GPI7 input to be used in the SET function"
		::= { vgp3000c01v1Entry 521 }

		-- 1.3.6.1.4.1.10106.3.101291.1.1.523
		vgp3000c01v1Gpo8SGpi8Ena OBJECT-TYPE
			SYNTAX Bit0No1Yes
			MAX-ACCESS read-write
			STATUS current
			DESCRIPTION
				"Enables the GPI8 input to be used in the SET function"
		::= { vgp3000c01v1Entry 523 }

		-- 1.3.6.1.4.1.10106.3.101291.1.1.525
		vgp3000c01v1Gpo8SGpi1Mode OBJECT-TYPE
			SYNTAX GpiMode
			MAX-ACCESS read-write
			STATUS current
			DESCRIPTION
				"Allows selecting the mode of GPI1 input in the SET function"
		::= { vgp3000c01v1Entry 525 }

		-- 1.3.6.1.4.1.10106.3.101291.1.1.527
		vgp3000c01v1Gpo8SGpi2Mode OBJECT-TYPE
			SYNTAX GpiMode
			MAX-ACCESS read-write
			STATUS current
			DESCRIPTION
				"Allows selecting the mode of GPI2 input in the SET function"
		::= { vgp3000c01v1Entry 527 }

		-- 1.3.6.1.4.1.10106.3.101291.1.1.529
		vgp3000c01v1Gpo8SGpi3Mode OBJECT-TYPE
			SYNTAX GpiMode
			MAX-ACCESS read-write
			STATUS current
			DESCRIPTION
				"Allows selecting the mode of GPI3 input in the SET function"
		::= { vgp3000c01v1Entry 529 }

		-- 1.3.6.1.4.1.10106.3.101291.1.1.531
		vgp3000c01v1Gpo8SGpi4Mode OBJECT-TYPE
			SYNTAX GpiMode
			MAX-ACCESS read-write
			STATUS current
			DESCRIPTION
				"Allows selecting the mode of GPI4 input in the SET function"
		::= { vgp3000c01v1Entry 531 }

		-- 1.3.6.1.4.1.10106.3.101291.1.1.533
		vgp3000c01v1Gpo8SGpi5Mode OBJECT-TYPE
			SYNTAX GpiMode
			MAX-ACCESS read-write
			STATUS current
			DESCRIPTION
				"Allows selecting the mode of GPI5 input in the SET function"
		::= { vgp3000c01v1Entry 533 }

		-- 1.3.6.1.4.1.10106.3.101291.1.1.535
		vgp3000c01v1Gpo8SGpi6Mode OBJECT-TYPE
			SYNTAX GpiMode
			MAX-ACCESS read-write
			STATUS current
			DESCRIPTION
				"Allows selecting the mode of GPI6 input in the SET function"
		::= { vgp3000c01v1Entry 535 }

		-- 1.3.6.1.4.1.10106.3.101291.1.1.537
		vgp3000c01v1Gpo8SGpi7Mode OBJECT-TYPE
			SYNTAX GpiMode
			MAX-ACCESS read-write
			STATUS current
			DESCRIPTION
				"Allows selecting the mode of GPI7 input in the SET function"
		::= { vgp3000c01v1Entry 537 }

		-- 1.3.6.1.4.1.10106.3.101291.1.1.539
		vgp3000c01v1Gpo8SGpi8Mode OBJECT-TYPE
			SYNTAX GpiMode
			MAX-ACCESS read-write
			STATUS current
			DESCRIPTION
				"Allows selecting the mode of GPI8 input in the SET function"
		::= { vgp3000c01v1Entry 539 }

		-- 1.3.6.1.4.1.10106.3.101291.1.1.541
		vgp3000c01v1Gpo8SDelay OBJECT-TYPE
			SYNTAX TimeX10Ms
			MAX-ACCESS read-write
			STATUS current
			DESCRIPTION
				"Allows adjusting the delay in SET function"
		::= { vgp3000c01v1Entry 541 }

		-- 1.3.6.1.4.1.10106.3.101291.1.1.543
		vgp3000c01v1Gpo8SF OBJECT-TYPE
			SYNTAX Bit0And1Or
			MAX-ACCESS read-write
			STATUS current
			DESCRIPTION
				"Allows selecting the type of the SET function"
		::= { vgp3000c01v1Entry 543 }

		-- 1.3.6.1.4.1.10106.3.101291.1.1.545
		vgp3000c01v1Gpo8RGpi1Ena OBJECT-TYPE
			SYNTAX Bit0No1Yes
			MAX-ACCESS read-write
			STATUS current
			DESCRIPTION
				"Enables the GPI1 input to be used in the RESET function"
		::= { vgp3000c01v1Entry 545 }

		-- 1.3.6.1.4.1.10106.3.101291.1.1.547
		vgp3000c01v1Gpo8RGpi2Ena OBJECT-TYPE
			SYNTAX Bit0No1Yes
			MAX-ACCESS read-write
			STATUS current
			DESCRIPTION
				"Enables the GPI2 input to be used in the RESET function"
		::= { vgp3000c01v1Entry 547 }

		-- 1.3.6.1.4.1.10106.3.101291.1.1.549
		vgp3000c01v1Gpo8RGpi3Ena OBJECT-TYPE
			SYNTAX Bit0No1Yes
			MAX-ACCESS read-write
			STATUS current
			DESCRIPTION
				"Enables the GPI3 input to be used in the RESET function"
		::= { vgp3000c01v1Entry 549 }

		-- 1.3.6.1.4.1.10106.3.101291.1.1.551
		vgp3000c01v1Gpo8RGpi4Ena OBJECT-TYPE
			SYNTAX Bit0No1Yes
			MAX-ACCESS read-write
			STATUS current
			DESCRIPTION
				"Enables the GPI4 input to be used in the RESET function"
		::= { vgp3000c01v1Entry 551 }

		-- 1.3.6.1.4.1.10106.3.101291.1.1.553
		vgp3000c01v1Gpo8RGpi5Ena OBJECT-TYPE
			SYNTAX Bit0No1Yes
			MAX-ACCESS read-write
			STATUS current
			DESCRIPTION
				"Enables the GPI5 input to be used in the RESET function"
		::= { vgp3000c01v1Entry 553 }

		-- 1.3.6.1.4.1.10106.3.101291.1.1.555
		vgp3000c01v1Gpo8RGpi6Ena OBJECT-TYPE
			SYNTAX Bit0No1Yes
			MAX-ACCESS read-write
			STATUS current
			DESCRIPTION
				"Enables the GPI6 input to be used in the RESET function"
		::= { vgp3000c01v1Entry 555 }

		-- 1.3.6.1.4.1.10106.3.101291.1.1.557
		vgp3000c01v1Gpo8RGpi7Ena OBJECT-TYPE
			SYNTAX Bit0No1Yes
			MAX-ACCESS read-write
			STATUS current
			DESCRIPTION
				"Enables the GPI7 input to be used in the RESET function"
		::= { vgp3000c01v1Entry 557 }

		-- 1.3.6.1.4.1.10106.3.101291.1.1.559
		vgp3000c01v1Gpo8RGpi8Ena OBJECT-TYPE
			SYNTAX Bit0No1Yes
			MAX-ACCESS read-write
			STATUS current
			DESCRIPTION
				"Enables the GPI8 input to be used in the RESET function"
		::= { vgp3000c01v1Entry 559 }

		-- 1.3.6.1.4.1.10106.3.101291.1.1.561
		vgp3000c01v1Gpo8RGpi1Mode OBJECT-TYPE
			SYNTAX GpiMode
			MAX-ACCESS read-write
			STATUS current
			DESCRIPTION
				"Allows selecting the mode of GPI1 input in the RESET function"
		::= { vgp3000c01v1Entry 561 }

		-- 1.3.6.1.4.1.10106.3.101291.1.1.563
		vgp3000c01v1Gpo8RGpi2Mode OBJECT-TYPE
			SYNTAX GpiMode
			MAX-ACCESS read-write
			STATUS current
			DESCRIPTION
				"Allows selecting the mode of GPI2 input in the RESET function"
		::= { vgp3000c01v1Entry 563 }

		-- 1.3.6.1.4.1.10106.3.101291.1.1.565
		vgp3000c01v1Gpo8RGpi3Mode OBJECT-TYPE
			SYNTAX GpiMode
			MAX-ACCESS read-write
			STATUS current
			DESCRIPTION
				"Allows selecting the mode of GPI3 input in the RESET function"
		::= { vgp3000c01v1Entry 565 }

		-- 1.3.6.1.4.1.10106.3.101291.1.1.567
		vgp3000c01v1Gpo8RGpi4Mode OBJECT-TYPE
			SYNTAX GpiMode
			MAX-ACCESS read-write
			STATUS current
			DESCRIPTION
				"Allows selecting the mode of GPI4 input in the RESET function"
		::= { vgp3000c01v1Entry 567 }

		-- 1.3.6.1.4.1.10106.3.101291.1.1.569
		vgp3000c01v1Gpo8RGpi5Mode OBJECT-TYPE
			SYNTAX GpiMode
			MAX-ACCESS read-write
			STATUS current
			DESCRIPTION
				"Allows selecting the mode of GPI5 input in the RESET function"
		::= { vgp3000c01v1Entry 569 }

		-- 1.3.6.1.4.1.10106.3.101291.1.1.571
		vgp3000c01v1Gpo8RGpi6Mode OBJECT-TYPE
			SYNTAX GpiMode
			MAX-ACCESS read-write
			STATUS current
			DESCRIPTION
				"Allows selecting the mode of GPI6 input in the RESET function"
		::= { vgp3000c01v1Entry 571 }

		-- 1.3.6.1.4.1.10106.3.101291.1.1.573
		vgp3000c01v1Gpo8RGpi7Mode OBJECT-TYPE
			SYNTAX GpiMode
			MAX-ACCESS read-write
			STATUS current
			DESCRIPTION
				"Allows selecting the mode of GPI7 input in the RESET function"
		::= { vgp3000c01v1Entry 573 }

		-- 1.3.6.1.4.1.10106.3.101291.1.1.575
		vgp3000c01v1Gpo8RGpi8Mode OBJECT-TYPE
			SYNTAX GpiMode
			MAX-ACCESS read-write
			STATUS current
			DESCRIPTION
				"Allows selecting the mode of GPI8 input in the RESET function"
		::= { vgp3000c01v1Entry 575 }

		-- 1.3.6.1.4.1.10106.3.101291.1.1.577
		vgp3000c01v1Gpo8RDelay OBJECT-TYPE
			SYNTAX TimeX10Ms
			MAX-ACCESS read-write
			STATUS current
			DESCRIPTION
				"Allows adjusting the delay in RESET function"
		::= { vgp3000c01v1Entry 577 }

		-- 1.3.6.1.4.1.10106.3.101291.1.1.579
		vgp3000c01v1Gpo8RF OBJECT-TYPE
			SYNTAX Bit0And1Or
			MAX-ACCESS read-write
			STATUS current
			DESCRIPTION
				"Allows selecting the type of the RESET function"
		::= { vgp3000c01v1Entry 579 }

		-- 1.3.6.1.4.1.10106.3.101291.1.1.581
		vgp3000c01v1Gpi1 OBJECT-TYPE
			SYNTAX Bit0Open1Clo
			MAX-ACCESS read-only
			STATUS current
			DESCRIPTION
				"Transmitted GPI1"
		::= { vgp3000c01v1Entry 581 }

		-- 1.3.6.1.4.1.10106.3.101291.1.1.582
		vgp3000c01v1Gpi1TrapEnable OBJECT-TYPE
			SYNTAX AlarmEnable
			MAX-ACCESS read-write
			STATUS current
			DESCRIPTION
				"Transmitted GPI1 Trap Enable"
		::= { vgp3000c01v1Entry 582 }

		-- 1.3.6.1.4.1.10106.3.101291.1.1.583
		vgp3000c01v1Gpi2 OBJECT-TYPE
			SYNTAX Bit0Open1Clo
			MAX-ACCESS read-only
			STATUS current
			DESCRIPTION
				"Transmitted GPI2"
		::= { vgp3000c01v1Entry 583 }

		-- 1.3.6.1.4.1.10106.3.101291.1.1.584
		vgp3000c01v1Gpi2TrapEnable OBJECT-TYPE
			SYNTAX AlarmEnable
			MAX-ACCESS read-write
			STATUS current
			DESCRIPTION
				"Transmitted GPI2 Trap Enable"
		::= { vgp3000c01v1Entry 584 }

		-- 1.3.6.1.4.1.10106.3.101291.1.1.585
		vgp3000c01v1Gpi3 OBJECT-TYPE
			SYNTAX Bit0Open1Clo
			MAX-ACCESS read-only
			STATUS current
			DESCRIPTION
				"Transmitted GPI3"
		::= { vgp3000c01v1Entry 585 }

		-- 1.3.6.1.4.1.10106.3.101291.1.1.586
		vgp3000c01v1Gpi3TrapEnable OBJECT-TYPE
			SYNTAX AlarmEnable
			MAX-ACCESS read-write
			STATUS current
			DESCRIPTION
				"Transmitted GPI3 Trap Enable"
		::= { vgp3000c01v1Entry 586 }

		-- 1.3.6.1.4.1.10106.3.101291.1.1.587
		vgp3000c01v1Gpi4 OBJECT-TYPE
			SYNTAX Bit0Open1Clo
			MAX-ACCESS read-only
			STATUS current
			DESCRIPTION
				"Transmitted GPI4"
		::= { vgp3000c01v1Entry 587 }

		-- 1.3.6.1.4.1.10106.3.101291.1.1.588
		vgp3000c01v1Gpi4TrapEnable OBJECT-TYPE
			SYNTAX AlarmEnable
			MAX-ACCESS read-write
			STATUS current
			DESCRIPTION
				"Transmitted GPI4 Trap Enable"
		::= { vgp3000c01v1Entry 588 }

		-- 1.3.6.1.4.1.10106.3.101291.1.1.589
		vgp3000c01v1Gpi5 OBJECT-TYPE
			SYNTAX Bit0Open1Clo
			MAX-ACCESS read-only
			STATUS current
			DESCRIPTION
				"Transmitted GPI5"
		::= { vgp3000c01v1Entry 589 }

		-- 1.3.6.1.4.1.10106.3.101291.1.1.590
		vgp3000c01v1Gpi5TrapEnable OBJECT-TYPE
			SYNTAX AlarmEnable
			MAX-ACCESS read-write
			STATUS current
			DESCRIPTION
				"Transmitted GPI5 Trap Enable"
		::= { vgp3000c01v1Entry 590 }

		-- 1.3.6.1.4.1.10106.3.101291.1.1.591
		vgp3000c01v1Gpi6 OBJECT-TYPE
			SYNTAX Bit0Open1Clo
			MAX-ACCESS read-only
			STATUS current
			DESCRIPTION
				"Transmitted GPI6"
		::= { vgp3000c01v1Entry 591 }

		-- 1.3.6.1.4.1.10106.3.101291.1.1.592
		vgp3000c01v1Gpi6TrapEnable OBJECT-TYPE
			SYNTAX AlarmEnable
			MAX-ACCESS read-write
			STATUS current
			DESCRIPTION
				"Transmitted GPI6 Trap Enable"
		::= { vgp3000c01v1Entry 592 }

		-- 1.3.6.1.4.1.10106.3.101291.1.1.593
		vgp3000c01v1Gpi7 OBJECT-TYPE
			SYNTAX Bit0Open1Clo
			MAX-ACCESS read-only
			STATUS current
			DESCRIPTION
				"Transmitted GPI7"
		::= { vgp3000c01v1Entry 593 }

		-- 1.3.6.1.4.1.10106.3.101291.1.1.594
		vgp3000c01v1Gpi7TrapEnable OBJECT-TYPE
			SYNTAX AlarmEnable
			MAX-ACCESS read-write
			STATUS current
			DESCRIPTION
				"Transmitted GPI7 Trap Enable"
		::= { vgp3000c01v1Entry 594 }

		-- 1.3.6.1.4.1.10106.3.101291.1.1.595
		vgp3000c01v1Gpi8 OBJECT-TYPE
			SYNTAX Bit0Open1Clo
			MAX-ACCESS read-only
			STATUS current
			DESCRIPTION
				"Transmitted GPI8"
		::= { vgp3000c01v1Entry 595 }

		-- 1.3.6.1.4.1.10106.3.101291.1.1.596
		vgp3000c01v1Gpi8TrapEnable OBJECT-TYPE
			SYNTAX AlarmEnable
			MAX-ACCESS read-write
			STATUS current
			DESCRIPTION
				"Transmitted GPI8 Trap Enable"
		::= { vgp3000c01v1Entry 596 }

		-- 1.3.6.1.4.1.10106.3.101291.1.1.597
		vgp3000c01v1Gpo1 OBJECT-TYPE
			SYNTAX Bit0Open1Clo
			MAX-ACCESS read-only
			STATUS current
			DESCRIPTION
				"Received GPO1"
		::= { vgp3000c01v1Entry 597 }

		-- 1.3.6.1.4.1.10106.3.101291.1.1.598
		vgp3000c01v1Gpo1TrapEnable OBJECT-TYPE
			SYNTAX AlarmEnable
			MAX-ACCESS read-write
			STATUS current
			DESCRIPTION
				"Received GPO1 Trap Enable"
		::= { vgp3000c01v1Entry 598 }

		-- 1.3.6.1.4.1.10106.3.101291.1.1.599
		vgp3000c01v1Gpo2 OBJECT-TYPE
			SYNTAX Bit0Open1Clo
			MAX-ACCESS read-only
			STATUS current
			DESCRIPTION
				"Received GPO2"
		::= { vgp3000c01v1Entry 599 }

		-- 1.3.6.1.4.1.10106.3.101291.1.1.600
		vgp3000c01v1Gpo2TrapEnable OBJECT-TYPE
			SYNTAX AlarmEnable
			MAX-ACCESS read-write
			STATUS current
			DESCRIPTION
				"Received GPO2 Trap Enable"
		::= { vgp3000c01v1Entry 600 }

		-- 1.3.6.1.4.1.10106.3.101291.1.1.601
		vgp3000c01v1Gpo3 OBJECT-TYPE
			SYNTAX Bit0Open1Clo
			MAX-ACCESS read-only
			STATUS current
			DESCRIPTION
				"Received GPO3"
		::= { vgp3000c01v1Entry 601 }

		-- 1.3.6.1.4.1.10106.3.101291.1.1.602
		vgp3000c01v1Gpo3TrapEnable OBJECT-TYPE
			SYNTAX AlarmEnable
			MAX-ACCESS read-write
			STATUS current
			DESCRIPTION
				"Received GPO3 Trap Enable"
		::= { vgp3000c01v1Entry 602 }

		-- 1.3.6.1.4.1.10106.3.101291.1.1.603
		vgp3000c01v1Gpo4 OBJECT-TYPE
			SYNTAX Bit0Open1Clo
			MAX-ACCESS read-only
			STATUS current
			DESCRIPTION
				"Received GPO4"
		::= { vgp3000c01v1Entry 603 }

		-- 1.3.6.1.4.1.10106.3.101291.1.1.604
		vgp3000c01v1Gpo4TrapEnable OBJECT-TYPE
			SYNTAX AlarmEnable
			MAX-ACCESS read-write
			STATUS current
			DESCRIPTION
				"Received GPO4 Trap Enable"
		::= { vgp3000c01v1Entry 604 }

		-- 1.3.6.1.4.1.10106.3.101291.1.1.605
		vgp3000c01v1Gpo5 OBJECT-TYPE
			SYNTAX Bit0Open1Clo
			MAX-ACCESS read-only
			STATUS current
			DESCRIPTION
				"Received GPO5"
		::= { vgp3000c01v1Entry 605 }

		-- 1.3.6.1.4.1.10106.3.101291.1.1.606
		vgp3000c01v1Gpo5TrapEnable OBJECT-TYPE
			SYNTAX AlarmEnable
			MAX-ACCESS read-write
			STATUS current
			DESCRIPTION
				"Received GPO5 Trap Enable"
		::= { vgp3000c01v1Entry 606 }

		-- 1.3.6.1.4.1.10106.3.101291.1.1.607
		vgp3000c01v1Gpo6 OBJECT-TYPE
			SYNTAX Bit0Open1Clo
			MAX-ACCESS read-only
			STATUS current
			DESCRIPTION
				"Received GPO6"
		::= { vgp3000c01v1Entry 607 }

		-- 1.3.6.1.4.1.10106.3.101291.1.1.608
		vgp3000c01v1Gpo6TrapEnable OBJECT-TYPE
			SYNTAX AlarmEnable
			MAX-ACCESS read-write
			STATUS current
			DESCRIPTION
				"Received GPO6 Trap Enable"
		::= { vgp3000c01v1Entry 608 }

		-- 1.3.6.1.4.1.10106.3.101291.1.1.609
		vgp3000c01v1Gpo7 OBJECT-TYPE
			SYNTAX Bit0Open1Clo
			MAX-ACCESS read-only
			STATUS current
			DESCRIPTION
				"Received GPO7"
		::= { vgp3000c01v1Entry 609 }

		-- 1.3.6.1.4.1.10106.3.101291.1.1.610
		vgp3000c01v1Gpo7TrapEnable OBJECT-TYPE
			SYNTAX AlarmEnable
			MAX-ACCESS read-write
			STATUS current
			DESCRIPTION
				"Received GPO7 Trap Enable"
		::= { vgp3000c01v1Entry 610 }

		-- 1.3.6.1.4.1.10106.3.101291.1.1.611
		vgp3000c01v1Gpo8 OBJECT-TYPE
			SYNTAX Bit0Open1Clo
			MAX-ACCESS read-only
			STATUS current
			DESCRIPTION
				"Received GPO8"
		::= { vgp3000c01v1Entry 611 }

		-- 1.3.6.1.4.1.10106.3.101291.1.1.612
		vgp3000c01v1Gpo8TrapEnable OBJECT-TYPE
			SYNTAX AlarmEnable
			MAX-ACCESS read-write
			STATUS current
			DESCRIPTION
				"Received GPO8 Trap Enable"
		::= { vgp3000c01v1Entry 612 }

		-- 1.3.6.1.4.1.10106.3.101291.1.1.613
		vgp3000c01v1SerialNo OBJECT-TYPE
			SYNTAX SerialNo
			MAX-ACCESS read-only
			STATUS current
			DESCRIPTION
				"Serial number"
		::= { vgp3000c01v1Entry 613 }

		-- 1.3.6.1.4.1.10106.3.403001
		ham3000c01v1 OBJECT IDENTIFIER ::= { albalaProducts 403001 }

		-- 1.3.6.1.4.1.10106.3.403001.1
		ham3000c01v1Table  OBJECT-TYPE
			SYNTAX SEQUENCE OF Ham3000c01v1Entry
			MAX-ACCESS not-accessible
			STATUS current
			DESCRIPTION
				"Module  HAM3000C01V1 Table"
			::= { ham3000c01v1 1 }

		-- 1.3.6.1.4.1.10106.3.403001.1.1
		ham3000c01v1Entry  OBJECT-TYPE
			SYNTAX Ham3000c01v1Entry
			MAX-ACCESS not-accessible
			STATUS current
			DESCRIPTION
				"Module HAM3000C01V1 Entry"
			INDEX { ham3000c01v1Index }
			::= { ham3000c01v1Table 1 }

			Ham3000c01v1Entry ::=
			SEQUENCE {
				ham3000c01v1Index
				ModuleIndex,
				ham3000c01v1ActivePreset
				Preset16Active,
				ham3000c01v1LoadPreset
				Preset16Load,
				ham3000c01v1SynchroMode
				Bit0Fra1Lin,
				ham3000c01v1FailMode
				Bit0Fre1Blk,
				ham3000c01v1DelayMode
				Bit0Syn1De2,
				ham3000c01v1HDelay
				DelayPixel5,
				ham3000c01v1FrameDelay
				DelayFram5,
				ham3000c01v1VDelay
				DelayLines2,
				ham3000c01v1MuxAuxC1
				AudioMxInput6,
				ham3000c01v1MuxAuxC2
				AudioMxInput6,
				ham3000c01v1MuxAuxC3
				AudioMxInput6,
				ham3000c01v1MuxAuxC4
				AudioMxInput6,
				ham3000c01v1FullScaleLev
				LevelDbu,
				ham3000c01v1OvldLevel
				LevelDbfs4,
				ham3000c01v1SilenceLevel
				LevelDbfs3,
				ham3000c01v1SilenceTime
				TimeS2,
				ham3000c01v1Gen1PipsTone
				Bit0Pips1Wav,
				ham3000c01v1Gen2PipsTone
				Bit0Pips1Wav,
				ham3000c01v1MediasGen1
				BitMask,
				ham3000c01v1MediasGen2
				BitMask,
				ham3000c01v1FreqPips1
				FrqGen,
				ham3000c01v1FreqPips2
				FrqGen,
				ham3000c01v1LevelPips1
				LevelDbfsD,
				ham3000c01v1LevelPips2
				LevelDbfsD,
				ham3000c01v1NPipsHour
				Uint4,
				ham3000c01v1NPipsHalf
				Uint4,
				ham3000c01v1ShortPerHour
				TimeX100Ms,
				ham3000c01v1ShortPerHalf
				TimeX100Ms,
				ham3000c01v1LongPerHour
				TimeX100Ms,
				ham3000c01v1LongPerHalf
				TimeX100Ms,
				ham3000c01v1EmbG1p0l
				AudioMxInputA,
				ham3000c01v1EmbG1p0lMonPh
				Bit0Nor1Inv,
				ham3000c01v1EmbG1p0lMono
				BitMask,
				ham3000c01v1EmbG1p0r
				AudioMxInputA,
				ham3000c01v1EmbG1p0rMonPh
				Bit0Nor1Inv,
				ham3000c01v1EmbG1p0rMono
				BitMask,
				ham3000c01v1EmbG1p1l
				AudioMxInputA,
				ham3000c01v1EmbG1p1lMonPh
				Bit0Nor1Inv,
				ham3000c01v1EmbG1p1lMono
				BitMask,
				ham3000c01v1EmbG1p1r
				AudioMxInputA,
				ham3000c01v1EmbG1p1rMonPh
				Bit0Nor1Inv,
				ham3000c01v1EmbG1p1rMono
				BitMask,
				ham3000c01v1EmbG2p0l
				AudioMxInputA,
				ham3000c01v1EmbG2p0lMonPh
				Bit0Nor1Inv,
				ham3000c01v1EmbG2p0lMono
				BitMask,
				ham3000c01v1EmbG2p0r
				AudioMxInputA,
				ham3000c01v1EmbG2p0rMonPh
				Bit0Nor1Inv,
				ham3000c01v1EmbG2p0rMono
				BitMask,
				ham3000c01v1EmbG2p1l
				AudioMxInputA,
				ham3000c01v1EmbG2p1lMonPh
				Bit0Nor1Inv,
				ham3000c01v1EmbG2p1lMono
				BitMask,
				ham3000c01v1EmbG2p1r
				AudioMxInputA,
				ham3000c01v1EmbG2p1rMonPh
				Bit0Nor1Inv,
				ham3000c01v1EmbG2p1rMono
				BitMask,
				ham3000c01v1EmbG3p0l
				AudioMxInputA,
				ham3000c01v1EmbG3p0lMonPh
				Bit0Nor1Inv,
				ham3000c01v1EmbG3p0lMono
				BitMask,
				ham3000c01v1EmbG3p0r
				AudioMxInputA,
				ham3000c01v1EmbG3p0rMonPh
				Bit0Nor1Inv,
				ham3000c01v1EmbG3p0rMono
				BitMask,
				ham3000c01v1EmbG3p1l
				AudioMxInputA,
				ham3000c01v1EmbG3p1lMonPh
				Bit0Nor1Inv,
				ham3000c01v1EmbG3p1lMono
				BitMask,
				ham3000c01v1EmbG3p1r
				AudioMxInputA,
				ham3000c01v1EmbG3p1rMonPh
				Bit0Nor1Inv,
				ham3000c01v1EmbG3p1rMono
				BitMask,
				ham3000c01v1EmbG4p0l
				AudioMxInputA,
				ham3000c01v1EmbG4p0lMonPh
				Bit0Nor1Inv,
				ham3000c01v1EmbG4p0lMono
				BitMask,
				ham3000c01v1EmbG4p0r
				AudioMxInputA,
				ham3000c01v1EmbG4p0rMonPh
				Bit0Nor1Inv,
				ham3000c01v1EmbG4p0rMono
				BitMask,
				ham3000c01v1EmbG4p1l
				AudioMxInputA,
				ham3000c01v1EmbG4p1lMonPh
				Bit0Nor1Inv,
				ham3000c01v1EmbG4p1lMono
				BitMask,
				ham3000c01v1EmbG4p1r
				AudioMxInputA,
				ham3000c01v1EmbG4p1rMonPh
				Bit0Nor1Inv,
				ham3000c01v1EmbG4p1rMono
				BitMask,
				ham3000c01v1AesOut1L
				AudioMxInputA,
				ham3000c01v1AesOut1lMonPh
				Bit0Nor1Inv,
				ham3000c01v1AesOut1lMono
				BitMask,
				ham3000c01v1AesOut1R
				AudioMxInputA,
				ham3000c01v1AesOut1rMonPh
				Bit0Nor1Inv,
				ham3000c01v1AesOut1rMono
				BitMask,
				ham3000c01v1AesOut2L
				AudioMxInputA,
				ham3000c01v1AesOut2lMonPh
				Bit0Nor1Inv,
				ham3000c01v1AesOut2lMono
				BitMask,
				ham3000c01v1AesOut2R
				AudioMxInputA,
				ham3000c01v1AesOut2rMonPh
				Bit0Nor1Inv,
				ham3000c01v1AesOut2rMono
				BitMask,
				ham3000c01v1GanG1p0l
				Gain24dbMute,
				ham3000c01v1PhaseG1p0l
				Bit0Nor1Inv,
				ham3000c01v1GanG1p0r
				Gain24dbMute,
				ham3000c01v1PhaseG1p0r
				Bit0Nor1Inv,
				ham3000c01v1GanG1p1l
				Gain24dbMute,
				ham3000c01v1PhaseG1p1l
				Bit0Nor1Inv,
				ham3000c01v1GanG1p1r
				Gain24dbMute,
				ham3000c01v1PhaseG1p1r
				Bit0Nor1Inv,
				ham3000c01v1GanG2p0l
				Gain24dbMute,
				ham3000c01v1PhaseG2p0l
				Bit0Nor1Inv,
				ham3000c01v1GanG2p0r
				Gain24dbMute,
				ham3000c01v1PhaseG2p0r
				Bit0Nor1Inv,
				ham3000c01v1GanG2p1l
				Gain24dbMute,
				ham3000c01v1PhaseG2p1l
				Bit0Nor1Inv,
				ham3000c01v1GanG2p1r
				Gain24dbMute,
				ham3000c01v1PhaseG2p1r
				Bit0Nor1Inv,
				ham3000c01v1GanG3p0l
				Gain24dbMute,
				ham3000c01v1PhaseG3p0l
				Bit0Nor1Inv,
				ham3000c01v1GanG3p0r
				Gain24dbMute,
				ham3000c01v1PhaseG3p0r
				Bit0Nor1Inv,
				ham3000c01v1GanG3p1l
				Gain24dbMute,
				ham3000c01v1PhaseG3p1l
				Bit0Nor1Inv,
				ham3000c01v1GanG3p1r
				Gain24dbMute,
				ham3000c01v1PhaseG3p1r
				Bit0Nor1Inv,
				ham3000c01v1GanG4p0l
				Gain24dbMute,
				ham3000c01v1PhaseG4p0l
				Bit0Nor1Inv,
				ham3000c01v1GanG4p0r
				Gain24dbMute,
				ham3000c01v1PhaseG4p0r
				Bit0Nor1Inv,
				ham3000c01v1GanG4p1l
				Gain24dbMute,
				ham3000c01v1PhaseG4p1l
				Bit0Nor1Inv,
				ham3000c01v1GanG4p1r
				Gain24dbMute,
				ham3000c01v1PhaseG4p1r
				Bit0Nor1Inv,
				ham3000c01v1GanAes1l
				Gain24dbMute,
				ham3000c01v1PhaseAes1l
				Bit0Nor1Inv,
				ham3000c01v1GanAes1r
				Gain24dbMute,
				ham3000c01v1PhaseAes1r
				Bit0Nor1Inv,
				ham3000c01v1GanAes2l
				Gain24dbMute,
				ham3000c01v1PhaseAes2l
				Bit0Nor1Inv,
				ham3000c01v1GanAes2r
				Gain24dbMute,
				ham3000c01v1PhaseAes2r
				Bit0Nor1Inv,
				ham3000c01v1DelayG1p0l
				DelayAud,
				ham3000c01v1DelayG1p0r
				DelayAud,
				ham3000c01v1DelayG1p1l
				DelayAud,
				ham3000c01v1DelayG1p1r
				DelayAud,
				ham3000c01v1DelayG2p0l
				DelayAud,
				ham3000c01v1DelayG2p0r
				DelayAud,
				ham3000c01v1DelayG2p1l
				DelayAud,
				ham3000c01v1DelayG2p1r
				DelayAud,
				ham3000c01v1DelayG3p0l
				DelayAud,
				ham3000c01v1DelayG3p0r
				DelayAud,
				ham3000c01v1DelayG3p1l
				DelayAud,
				ham3000c01v1DelayG3p1r
				DelayAud,
				ham3000c01v1DelayG4p0l
				DelayAud,
				ham3000c01v1DelayG4p0r
				DelayAud,
				ham3000c01v1DelayG4p1l
				DelayAud,
				ham3000c01v1DelayG4p1r
				DelayAud,
				ham3000c01v1DelayAes1l
				DelayAud,
				ham3000c01v1DelayAes1r
				DelayAud,
				ham3000c01v1DelayAes2l
				DelayAud,
				ham3000c01v1DelayAes2r
				DelayAud,
				ham3000c01v1StatFlash
				BitFailN,
				ham3000c01v1NoSignalMain
				BitFail,
				ham3000c01v1NoSignalMainTrapEnable
				AlarmEnable,
				ham3000c01v1UnlockMain
				BitFail,
				ham3000c01v1UnlockMainTrapEnable
				AlarmEnable,
				ham3000c01v1EdhErrorMain
				BitFail,
				ham3000c01v1EdhErrorMainTrapEnable
				AlarmEnable,
				ham3000c01v1NoSignalAux
				BitFail,
				ham3000c01v1UnlockAux
				BitFail,
				ham3000c01v1EdhErrorAux
				BitFail,
				ham3000c01v1RefAbsent
				BitFail,
				ham3000c01v1RefAbsentTrapEnable
				AlarmEnable,
				ham3000c01v1RefUnlock
				BitFail,
				ham3000c01v1RefUnlockTrapEnable
				AlarmEnable,
				ham3000c01v1FormatMainIn
				SdiHd3gFmt3,
				ham3000c01v1FormatAuxIn
				SdiHd3gFmt3,
				ham3000c01v1FormatRef
				SdiHd3gFmt3,
				ham3000c01v1FormatMainTx
				SdiHd3gFmt3,
				ham3000c01v1SigDelay
				DelayX20Us,
				ham3000c01v1Gr1MainPres
				Bit0No1Yes,
				ham3000c01v1Gr1MainPresTrapEnable
				AlarmEnable,
				ham3000c01v1Gr2MainPres
				Bit0No1Yes,
				ham3000c01v1Gr2MainPresTrapEnable
				AlarmEnable,
				ham3000c01v1Gr3MainPres
				Bit0No1Yes,
				ham3000c01v1Gr3MainPresTrapEnable
				AlarmEnable,
				ham3000c01v1Gr4MainPres
				Bit0No1Yes,
				ham3000c01v1Gr4MainPresTrapEnable
				AlarmEnable,
				ham3000c01v1Gr1AuxPres
				Bit0No1Yes,
				ham3000c01v1Gr2AuxPres
				Bit0No1Yes,
				ham3000c01v1Gr3AuxPres
				Bit0No1Yes,
				ham3000c01v1Gr4AuxPres
				Bit0No1Yes,
				ham3000c01v1Aes1Ok
				BitFailN,
				ham3000c01v1Aes1Frq
				AudioSelFreq6,
				ham3000c01v1Aes2Ok
				BitFailN,
				ham3000c01v1Aes2Frq
				AudioSelFreq6,
				ham3000c01v1AudStatMain
				BitFail,
				ham3000c01v1AudStatMainTrapEnable
				AlarmEnable,
				ham3000c01v1AudStatAux
				BitFail,
				ham3000c01v1AudStatAuxTrapEnable
				AlarmEnable,
				ham3000c01v1AudStatAes1
				BitFail,
				ham3000c01v1AudStatAes1TrapEnable
				AlarmEnable,
				ham3000c01v1AudStatAes2
				BitFail,
				ham3000c01v1AudStatAes2TrapEnable
				AlarmEnable,
				ham3000c01v1OvldPgmOut
				BitFail,
				ham3000c01v1OvldPgmOutTrapEnable
				AlarmEnable,
				ham3000c01v1OvldAes1Out
				BitFail,
				ham3000c01v1OvldAes1OutTrapEnable
				AlarmEnable,
				ham3000c01v1OvldAes2Out
				BitFail,
				ham3000c01v1OvldAes2OutTrapEnable
				AlarmEnable,
				ham3000c01v1SilPgmOut
				BitFail,
				ham3000c01v1SilPgmOutTrapEnable
				AlarmEnable,
				ham3000c01v1SilAes1Out
				BitFail,
				ham3000c01v1SilAes1OutTrapEnable
				AlarmEnable,
				ham3000c01v1SilAes2Out
				BitFail,
				ham3000c01v1SilAes2OutTrapEnable
				AlarmEnable,
				ham3000c01v1SerialNo
				SerialNo,
				ham3000c01v1SavePreset
				Preset16Save,
				ham3000c01v1VidAuxSel
				Bit0Aux1Pgm
			 }

		-- 1.3.6.1.4.1.10106.3.101291.1.1.1
		ham3000c01v1Index OBJECT-TYPE
			SYNTAX ModuleIndex
			MAX-ACCESS read-only
			STATUS current
			DESCRIPTION
				"Index of HAM3000C01V1 Table"
		::= { ham3000c01v1Entry 1 }

		-- 1.3.6.1.4.1.10106.3.101291.1.1.3
		ham3000c01v1ActivePreset OBJECT-TYPE
			SYNTAX Preset16Active
			MAX-ACCESS read-only
			STATUS current
			DESCRIPTION
				"Shows the active preset"
		::= { ham3000c01v1Entry 3 }

		-- 1.3.6.1.4.1.10106.3.101291.1.1.5
		ham3000c01v1LoadPreset OBJECT-TYPE
			SYNTAX Preset16Load
			MAX-ACCESS read-write
			STATUS current
			DESCRIPTION
				"Allows loading a preset"
		::= { ham3000c01v1Entry 5 }

		-- 1.3.6.1.4.1.10106.3.101291.1.1.7
		ham3000c01v1SynchroMode OBJECT-TYPE
			SYNTAX Bit0Fra1Lin
			MAX-ACCESS read-write
			STATUS current
			DESCRIPTION
				"Allows selecting the synchronizing mode"
		::= { ham3000c01v1Entry 7 }

		-- 1.3.6.1.4.1.10106.3.101291.1.1.9
		ham3000c01v1FailMode OBJECT-TYPE
			SYNTAX Bit0Fre1Blk
			MAX-ACCESS read-write
			STATUS current
			DESCRIPTION
				"Allows selecting the output video signal if the input fails"
		::= { ham3000c01v1Entry 9 }

		-- 1.3.6.1.4.1.10106.3.101291.1.1.11
		ham3000c01v1DelayMode OBJECT-TYPE
			SYNTAX Bit0Syn1De2
			MAX-ACCESS read-write
			STATUS current
			DESCRIPTION
				"Allows selecting the operating mode"
		::= { ham3000c01v1Entry 11 }

		-- 1.3.6.1.4.1.10106.3.101291.1.1.13
		ham3000c01v1HDelay OBJECT-TYPE
			SYNTAX DelayPixel5
			MAX-ACCESS read-write
			STATUS current
			DESCRIPTION
				"Allows adjusting the video horizontal delay"
		::= { ham3000c01v1Entry 13 }

		-- 1.3.6.1.4.1.10106.3.101291.1.1.15
		ham3000c01v1FrameDelay OBJECT-TYPE
			SYNTAX DelayFram5
			MAX-ACCESS read-write
			STATUS current
			DESCRIPTION
				"Allows adjusting the frame delay"
		::= { ham3000c01v1Entry 15 }

		-- 1.3.6.1.4.1.10106.3.101291.1.1.17
		ham3000c01v1VDelay OBJECT-TYPE
			SYNTAX DelayLines2
			MAX-ACCESS read-write
			STATUS current
			DESCRIPTION
				"Allows adjusting the video vertical delay"
		::= { ham3000c01v1Entry 17 }

		-- 1.3.6.1.4.1.10106.3.101291.1.1.19
		ham3000c01v1MuxAuxC1 OBJECT-TYPE
			SYNTAX AudioMxInput6
			MAX-ACCESS read-write
			STATUS current
			DESCRIPTION
				"Selects the channel 1 from the input video signal AUX IN"
		::= { ham3000c01v1Entry 19 }

		-- 1.3.6.1.4.1.10106.3.101291.1.1.21
		ham3000c01v1MuxAuxC2 OBJECT-TYPE
			SYNTAX AudioMxInput6
			MAX-ACCESS read-write
			STATUS current
			DESCRIPTION
				"Selects the channel 2 from the input video signal AUX IN"
		::= { ham3000c01v1Entry 21 }

		-- 1.3.6.1.4.1.10106.3.101291.1.1.23
		ham3000c01v1MuxAuxC3 OBJECT-TYPE
			SYNTAX AudioMxInput6
			MAX-ACCESS read-write
			STATUS current
			DESCRIPTION
				"Selects the channel 3 from the input video signal AUX IN"
		::= { ham3000c01v1Entry 23 }

		-- 1.3.6.1.4.1.10106.3.101291.1.1.25
		ham3000c01v1MuxAuxC4 OBJECT-TYPE
			SYNTAX AudioMxInput6
			MAX-ACCESS read-write
			STATUS current
			DESCRIPTION
				"Selects the channel 4 from the input video signal AUX IN"
		::= { ham3000c01v1Entry 25 }

		-- 1.3.6.1.4.1.10106.3.101291.1.1.27
		ham3000c01v1FullScaleLev OBJECT-TYPE
			SYNTAX LevelDbu
			MAX-ACCESS read-write
			STATUS current
			DESCRIPTION
				"Full scale level"
		::= { ham3000c01v1Entry 27 }

		-- 1.3.6.1.4.1.10106.3.101291.1.1.29
		ham3000c01v1OvldLevel OBJECT-TYPE
			SYNTAX LevelDbfs4
			MAX-ACCESS read-write
			STATUS current
			DESCRIPTION
				"Allows adjusting the threshold level for the overload detector"
		::= { ham3000c01v1Entry 29 }

		-- 1.3.6.1.4.1.10106.3.101291.1.1.31
		ham3000c01v1SilenceLevel OBJECT-TYPE
			SYNTAX LevelDbfs3
			MAX-ACCESS read-write
			STATUS current
			DESCRIPTION
				"Allows adjusting the threshold level for the silence detector"
		::= { ham3000c01v1Entry 31 }

		-- 1.3.6.1.4.1.10106.3.101291.1.1.33
		ham3000c01v1SilenceTime OBJECT-TYPE
			SYNTAX TimeS2
			MAX-ACCESS read-write
			STATUS current
			DESCRIPTION
				"Allows adjusting the silence time"
		::= { ham3000c01v1Entry 33 }

		-- 1.3.6.1.4.1.10106.3.101291.1.1.35
		ham3000c01v1Gen1PipsTone OBJECT-TYPE
			SYNTAX Bit0Pips1Wav
			MAX-ACCESS read-write
			STATUS current
			DESCRIPTION
				"Selects the type of signal to be generated at channel 1 of the generator: Greenwich Time Signals (Pips) or a sinewave"
		::= { ham3000c01v1Entry 35 }

		-- 1.3.6.1.4.1.10106.3.101291.1.1.37
		ham3000c01v1Gen2PipsTone OBJECT-TYPE
			SYNTAX Bit0Pips1Wav
			MAX-ACCESS read-write
			STATUS current
			DESCRIPTION
				"Selects the type of signal to be generated at channel 2 of the generator: Greenwich Time Signals (Pips) or a sinewave"
		::= { ham3000c01v1Entry 37 }

		-- 1.3.6.1.4.1.10106.3.101291.1.1.39
		ham3000c01v1MediasGen1 OBJECT-TYPE
			SYNTAX BitMask
			MAX-ACCESS read-write
			STATUS current
			DESCRIPTION
				"Enables the pips sounding at half past at channel 1 of the generator"
		::= { ham3000c01v1Entry 39 }

		-- 1.3.6.1.4.1.10106.3.101291.1.1.41
		ham3000c01v1MediasGen2 OBJECT-TYPE
			SYNTAX BitMask
			MAX-ACCESS read-write
			STATUS current
			DESCRIPTION
				"Enables the pips sounding at half past at channel 2 of the generator"
		::= { ham3000c01v1Entry 41 }

		-- 1.3.6.1.4.1.10106.3.101291.1.1.43
		ham3000c01v1FreqPips1 OBJECT-TYPE
			SYNTAX FrqGen
			MAX-ACCESS read-write
			STATUS current
			DESCRIPTION
				"Frequency of the sound signals generated at channel 1"
		::= { ham3000c01v1Entry 43 }

		-- 1.3.6.1.4.1.10106.3.101291.1.1.45
		ham3000c01v1FreqPips2 OBJECT-TYPE
			SYNTAX FrqGen
			MAX-ACCESS read-write
			STATUS current
			DESCRIPTION
				"Frequency of the sound singals generated at channel 2"
		::= { ham3000c01v1Entry 45 }

		-- 1.3.6.1.4.1.10106.3.101291.1.1.47
		ham3000c01v1LevelPips1 OBJECT-TYPE
			SYNTAX LevelDbfsD
			MAX-ACCESS read-write
			STATUS current
			DESCRIPTION
				"Amplitude of the sound signals generated at channel 1"
		::= { ham3000c01v1Entry 47 }

		-- 1.3.6.1.4.1.10106.3.101291.1.1.49
		ham3000c01v1LevelPips2 OBJECT-TYPE
			SYNTAX LevelDbfsD
			MAX-ACCESS read-write
			STATUS current
			DESCRIPTION
				"Amplitude of the sound signals generated at channel 2"
		::= { ham3000c01v1Entry 49 }

		-- 1.3.6.1.4.1.10106.3.101291.1.1.51
		ham3000c01v1NPipsHour OBJECT-TYPE
			SYNTAX Uint4
			MAX-ACCESS read-write
			STATUS current
			DESCRIPTION
				"Number of short pips generated at o'clock"
		::= { ham3000c01v1Entry 51 }

		-- 1.3.6.1.4.1.10106.3.101291.1.1.53
		ham3000c01v1NPipsHalf OBJECT-TYPE
			SYNTAX Uint4
			MAX-ACCESS read-write
			STATUS current
			DESCRIPTION
				"Number of short pips generated at half past"
		::= { ham3000c01v1Entry 53 }

		-- 1.3.6.1.4.1.10106.3.101291.1.1.55
		ham3000c01v1ShortPerHour OBJECT-TYPE
			SYNTAX TimeX100Ms
			MAX-ACCESS read-write
			STATUS current
			DESCRIPTION
				"Length of o'clock short pips"
		::= { ham3000c01v1Entry 55 }

		-- 1.3.6.1.4.1.10106.3.101291.1.1.57
		ham3000c01v1ShortPerHalf OBJECT-TYPE
			SYNTAX TimeX100Ms
			MAX-ACCESS read-write
			STATUS current
			DESCRIPTION
				"Length of half past short pips"
		::= { ham3000c01v1Entry 57 }

		-- 1.3.6.1.4.1.10106.3.101291.1.1.59
		ham3000c01v1LongPerHour OBJECT-TYPE
			SYNTAX TimeX100Ms
			MAX-ACCESS read-write
			STATUS current
			DESCRIPTION
				"Length of o'clock long pip"
		::= { ham3000c01v1Entry 59 }

		-- 1.3.6.1.4.1.10106.3.101291.1.1.61
		ham3000c01v1LongPerHalf OBJECT-TYPE
			SYNTAX TimeX100Ms
			MAX-ACCESS read-write
			STATUS current
			DESCRIPTION
				"Length of half past long pip"
		::= { ham3000c01v1Entry 61 }

		-- 1.3.6.1.4.1.10106.3.101291.1.1.63
		ham3000c01v1EmbG1p0l OBJECT-TYPE
			SYNTAX AudioMxInputA
			MAX-ACCESS read-write
			STATUS current
			DESCRIPTION
				"Audio channel assignment to the audio channel embedded in G1P0L PGM OUT"
		::= { ham3000c01v1Entry 63 }

		-- 1.3.6.1.4.1.10106.3.101291.1.1.65
		ham3000c01v1EmbG1p0lMonPh OBJECT-TYPE
			SYNTAX Bit0Nor1Inv
			MAX-ACCESS read-write
			STATUS current
			DESCRIPTION
				"Phase applied to the secundary channel in the stereophonic audio pair for generating the monophonic audio in G1P0L PGM OUT"
		::= { ham3000c01v1Entry 65 }

		-- 1.3.6.1.4.1.10106.3.101291.1.1.67
		ham3000c01v1EmbG1p0lMono OBJECT-TYPE
			SYNTAX BitMask
			MAX-ACCESS read-write
			STATUS current
			DESCRIPTION
				"Monophonic audio generated from the audio pair assigned to G1P0L PGM OUT"
		::= { ham3000c01v1Entry 67 }

		-- 1.3.6.1.4.1.10106.3.101291.1.1.69
		ham3000c01v1EmbG1p0r OBJECT-TYPE
			SYNTAX AudioMxInputA
			MAX-ACCESS read-write
			STATUS current
			DESCRIPTION
				"Audio channel assignment to the audio channel embedded in G1P0R PGM OUT"
		::= { ham3000c01v1Entry 69 }

		-- 1.3.6.1.4.1.10106.3.101291.1.1.71
		ham3000c01v1EmbG1p0rMonPh OBJECT-TYPE
			SYNTAX Bit0Nor1Inv
			MAX-ACCESS read-write
			STATUS current
			DESCRIPTION
				"Phase applied to the secundary channel in the stereophonic audio pair for generating the monophonic audio in G1P0R PGM OUT"
		::= { ham3000c01v1Entry 71 }

		-- 1.3.6.1.4.1.10106.3.101291.1.1.73
		ham3000c01v1EmbG1p0rMono OBJECT-TYPE
			SYNTAX BitMask
			MAX-ACCESS read-write
			STATUS current
			DESCRIPTION
				"Monophonic audio generated from the audio pair assigned to G1P0R PGM OUT"
		::= { ham3000c01v1Entry 73 }

		-- 1.3.6.1.4.1.10106.3.101291.1.1.75
		ham3000c01v1EmbG1p1l OBJECT-TYPE
			SYNTAX AudioMxInputA
			MAX-ACCESS read-write
			STATUS current
			DESCRIPTION
				"Audio channel assignment to the audio channel embedded in G1P1L PGM OUT"
		::= { ham3000c01v1Entry 75 }

		-- 1.3.6.1.4.1.10106.3.101291.1.1.77
		ham3000c01v1EmbG1p1lMonPh OBJECT-TYPE
			SYNTAX Bit0Nor1Inv
			MAX-ACCESS read-write
			STATUS current
			DESCRIPTION
				"Phase applied to the secundary channel in the stereophonic audio pair for generating the monophonic audio in G1P1L PGM OUT"
		::= { ham3000c01v1Entry 77 }

		-- 1.3.6.1.4.1.10106.3.101291.1.1.79
		ham3000c01v1EmbG1p1lMono OBJECT-TYPE
			SYNTAX BitMask
			MAX-ACCESS read-write
			STATUS current
			DESCRIPTION
				"Monophonic audio generated from the audio pair assigned to G1P1L PGM OUT"
		::= { ham3000c01v1Entry 79 }

		-- 1.3.6.1.4.1.10106.3.101291.1.1.81
		ham3000c01v1EmbG1p1r OBJECT-TYPE
			SYNTAX AudioMxInputA
			MAX-ACCESS read-write
			STATUS current
			DESCRIPTION
				"Audio channel assignment to the audio channel embedded in G1P1R PGM OUT"
		::= { ham3000c01v1Entry 81 }

		-- 1.3.6.1.4.1.10106.3.101291.1.1.83
		ham3000c01v1EmbG1p1rMonPh OBJECT-TYPE
			SYNTAX Bit0Nor1Inv
			MAX-ACCESS read-write
			STATUS current
			DESCRIPTION
				"Phase applied to the secundary channel in the stereophonic audio pair for generating the monophonic audio in G1P1R PGM OUT"
		::= { ham3000c01v1Entry 83 }

		-- 1.3.6.1.4.1.10106.3.101291.1.1.85
		ham3000c01v1EmbG1p1rMono OBJECT-TYPE
			SYNTAX BitMask
			MAX-ACCESS read-write
			STATUS current
			DESCRIPTION
				"Monophonic audio generated from the audio pair assigned to G1P1R PGM OUT"
		::= { ham3000c01v1Entry 85 }

		-- 1.3.6.1.4.1.10106.3.101291.1.1.87
		ham3000c01v1EmbG2p0l OBJECT-TYPE
			SYNTAX AudioMxInputA
			MAX-ACCESS read-write
			STATUS current
			DESCRIPTION
				"Audio channel assignment to the audio channel embedded in G2P0L PGM OUT"
		::= { ham3000c01v1Entry 87 }

		-- 1.3.6.1.4.1.10106.3.101291.1.1.89
		ham3000c01v1EmbG2p0lMonPh OBJECT-TYPE
			SYNTAX Bit0Nor1Inv
			MAX-ACCESS read-write
			STATUS current
			DESCRIPTION
				"Phase applied to the secundary channel in the stereophonic audio pair for generating the monophonic audio in G2P0L PGM OUT"
		::= { ham3000c01v1Entry 89 }

		-- 1.3.6.1.4.1.10106.3.101291.1.1.91
		ham3000c01v1EmbG2p0lMono OBJECT-TYPE
			SYNTAX BitMask
			MAX-ACCESS read-write
			STATUS current
			DESCRIPTION
				"Monophonic audio generated from the audio pair assigned to G2P0L PGM OUT"
		::= { ham3000c01v1Entry 91 }

		-- 1.3.6.1.4.1.10106.3.101291.1.1.93
		ham3000c01v1EmbG2p0r OBJECT-TYPE
			SYNTAX AudioMxInputA
			MAX-ACCESS read-write
			STATUS current
			DESCRIPTION
				"Audio channel assignment to the audio channel embedded in G2P0R PGM OUT"
		::= { ham3000c01v1Entry 93 }

		-- 1.3.6.1.4.1.10106.3.101291.1.1.95
		ham3000c01v1EmbG2p0rMonPh OBJECT-TYPE
			SYNTAX Bit0Nor1Inv
			MAX-ACCESS read-write
			STATUS current
			DESCRIPTION
				"Phase applied to the secundary channel in the stereophonic audio pair for generating the monophonic audio in G2P0R PGM OUT"
		::= { ham3000c01v1Entry 95 }

		-- 1.3.6.1.4.1.10106.3.101291.1.1.97
		ham3000c01v1EmbG2p0rMono OBJECT-TYPE
			SYNTAX BitMask
			MAX-ACCESS read-write
			STATUS current
			DESCRIPTION
				"Monophonic audio generated from the audio pair assigned to G2P0R PGM OUT"
		::= { ham3000c01v1Entry 97 }

		-- 1.3.6.1.4.1.10106.3.101291.1.1.99
		ham3000c01v1EmbG2p1l OBJECT-TYPE
			SYNTAX AudioMxInputA
			MAX-ACCESS read-write
			STATUS current
			DESCRIPTION
				"Audio channel assignment to the audio channel embedded in G2P1L PGM OUT"
		::= { ham3000c01v1Entry 99 }

		-- 1.3.6.1.4.1.10106.3.101291.1.1.101
		ham3000c01v1EmbG2p1lMonPh OBJECT-TYPE
			SYNTAX Bit0Nor1Inv
			MAX-ACCESS read-write
			STATUS current
			DESCRIPTION
				"Phase applied to the secundary channel in the stereophonic audio pair for generating the monophonic audio in G2P1L PGM OUT"
		::= { ham3000c01v1Entry 101 }

		-- 1.3.6.1.4.1.10106.3.101291.1.1.103
		ham3000c01v1EmbG2p1lMono OBJECT-TYPE
			SYNTAX BitMask
			MAX-ACCESS read-write
			STATUS current
			DESCRIPTION
				"Monophonic audio generated from the audio pair assigned to G2P1L PGM OUT"
		::= { ham3000c01v1Entry 103 }

		-- 1.3.6.1.4.1.10106.3.101291.1.1.105
		ham3000c01v1EmbG2p1r OBJECT-TYPE
			SYNTAX AudioMxInputA
			MAX-ACCESS read-write
			STATUS current
			DESCRIPTION
				"Audio channel assignment to the audio channel embedded in G2P1R PGM OUT"
		::= { ham3000c01v1Entry 105 }

		-- 1.3.6.1.4.1.10106.3.101291.1.1.107
		ham3000c01v1EmbG2p1rMonPh OBJECT-TYPE
			SYNTAX Bit0Nor1Inv
			MAX-ACCESS read-write
			STATUS current
			DESCRIPTION
				"Phase applied to the secundary channel in the stereophonic audio pair for generating the monophonic audio in G2P1R PGM OUT"
		::= { ham3000c01v1Entry 107 }

		-- 1.3.6.1.4.1.10106.3.101291.1.1.109
		ham3000c01v1EmbG2p1rMono OBJECT-TYPE
			SYNTAX BitMask
			MAX-ACCESS read-write
			STATUS current
			DESCRIPTION
				"Monophonic audio generated from the audio pair assigned to G2P1R PGM OUT"
		::= { ham3000c01v1Entry 109 }

		-- 1.3.6.1.4.1.10106.3.101291.1.1.111
		ham3000c01v1EmbG3p0l OBJECT-TYPE
			SYNTAX AudioMxInputA
			MAX-ACCESS read-write
			STATUS current
			DESCRIPTION
				"Audio channel assignment to the audio channel embedded in G3P0L PGM OUT"
		::= { ham3000c01v1Entry 111 }

		-- 1.3.6.1.4.1.10106.3.101291.1.1.113
		ham3000c01v1EmbG3p0lMonPh OBJECT-TYPE
			SYNTAX Bit0Nor1Inv
			MAX-ACCESS read-write
			STATUS current
			DESCRIPTION
				"Phase applied to the secundary channel in the stereophonic audio pair for generating the monophonic audio in G3P0L PGM OUT"
		::= { ham3000c01v1Entry 113 }

		-- 1.3.6.1.4.1.10106.3.101291.1.1.115
		ham3000c01v1EmbG3p0lMono OBJECT-TYPE
			SYNTAX BitMask
			MAX-ACCESS read-write
			STATUS current
			DESCRIPTION
				"Monophonic audio generated from the audio pair assigned to G3P0L PGM OUT"
		::= { ham3000c01v1Entry 115 }

		-- 1.3.6.1.4.1.10106.3.101291.1.1.117
		ham3000c01v1EmbG3p0r OBJECT-TYPE
			SYNTAX AudioMxInputA
			MAX-ACCESS read-write
			STATUS current
			DESCRIPTION
				"Audio channel assignment to the audio channel embedded in G3P0R PGM OUT"
		::= { ham3000c01v1Entry 117 }

		-- 1.3.6.1.4.1.10106.3.101291.1.1.119
		ham3000c01v1EmbG3p0rMonPh OBJECT-TYPE
			SYNTAX Bit0Nor1Inv
			MAX-ACCESS read-write
			STATUS current
			DESCRIPTION
				"Phase applied to the secundary channel in the stereophonic audio pair for generating the monophonic audio in G3P0R PGM OUT"
		::= { ham3000c01v1Entry 119 }

		-- 1.3.6.1.4.1.10106.3.101291.1.1.121
		ham3000c01v1EmbG3p0rMono OBJECT-TYPE
			SYNTAX BitMask
			MAX-ACCESS read-write
			STATUS current
			DESCRIPTION
				"Monophonic audio generated from the audio pair assigned to G3P0R PGM OUT"
		::= { ham3000c01v1Entry 121 }

		-- 1.3.6.1.4.1.10106.3.101291.1.1.123
		ham3000c01v1EmbG3p1l OBJECT-TYPE
			SYNTAX AudioMxInputA
			MAX-ACCESS read-write
			STATUS current
			DESCRIPTION
				"Audio channel assignment to the audio channel embedded in G3P1L PGM OUT"
		::= { ham3000c01v1Entry 123 }

		-- 1.3.6.1.4.1.10106.3.101291.1.1.125
		ham3000c01v1EmbG3p1lMonPh OBJECT-TYPE
			SYNTAX Bit0Nor1Inv
			MAX-ACCESS read-write
			STATUS current
			DESCRIPTION
				"Phase applied to the secundary channel in the stereophonic audio pair for generating the monophonic audio in G3P1L PGM OUT"
		::= { ham3000c01v1Entry 125 }

		-- 1.3.6.1.4.1.10106.3.101291.1.1.127
		ham3000c01v1EmbG3p1lMono OBJECT-TYPE
			SYNTAX BitMask
			MAX-ACCESS read-write
			STATUS current
			DESCRIPTION
				"Monophonic audio generated from the audio pair assigned to G3P1L PGM OUT"
		::= { ham3000c01v1Entry 127 }

		-- 1.3.6.1.4.1.10106.3.101291.1.1.129
		ham3000c01v1EmbG3p1r OBJECT-TYPE
			SYNTAX AudioMxInputA
			MAX-ACCESS read-write
			STATUS current
			DESCRIPTION
				"Audio channel assignment to the audio channel embedded in G3P1R PGM OUT"
		::= { ham3000c01v1Entry 129 }

		-- 1.3.6.1.4.1.10106.3.101291.1.1.131
		ham3000c01v1EmbG3p1rMonPh OBJECT-TYPE
			SYNTAX Bit0Nor1Inv
			MAX-ACCESS read-write
			STATUS current
			DESCRIPTION
				"Phase applied to the secundary channel in the stereophonic audio pair for generating the monophonic audio in G3P1R PGM OUT"
		::= { ham3000c01v1Entry 131 }

		-- 1.3.6.1.4.1.10106.3.101291.1.1.133
		ham3000c01v1EmbG3p1rMono OBJECT-TYPE
			SYNTAX BitMask
			MAX-ACCESS read-write
			STATUS current
			DESCRIPTION
				"Monophonic audio generated from the audio pair assigned to G3P1R PGM OUT"
		::= { ham3000c01v1Entry 133 }

		-- 1.3.6.1.4.1.10106.3.101291.1.1.135
		ham3000c01v1EmbG4p0l OBJECT-TYPE
			SYNTAX AudioMxInputA
			MAX-ACCESS read-write
			STATUS current
			DESCRIPTION
				"Audio channel assignment to the audio channel embedded in G4P0L PGM OUT"
		::= { ham3000c01v1Entry 135 }

		-- 1.3.6.1.4.1.10106.3.101291.1.1.137
		ham3000c01v1EmbG4p0lMonPh OBJECT-TYPE
			SYNTAX Bit0Nor1Inv
			MAX-ACCESS read-write
			STATUS current
			DESCRIPTION
				"Phase applied to the secundary channel in the stereophonic audio pair for generating the monophonic audio in G4P0L PGM OUT"
		::= { ham3000c01v1Entry 137 }

		-- 1.3.6.1.4.1.10106.3.101291.1.1.139
		ham3000c01v1EmbG4p0lMono OBJECT-TYPE
			SYNTAX BitMask
			MAX-ACCESS read-write
			STATUS current
			DESCRIPTION
				"Monophonic audio generated from the audio pair assigned to G4P0L PGM OUT"
		::= { ham3000c01v1Entry 139 }

		-- 1.3.6.1.4.1.10106.3.101291.1.1.141
		ham3000c01v1EmbG4p0r OBJECT-TYPE
			SYNTAX AudioMxInputA
			MAX-ACCESS read-write
			STATUS current
			DESCRIPTION
				"Audio channel assignment to the audio channel embedded in G4P0R PGM OUT"
		::= { ham3000c01v1Entry 141 }

		-- 1.3.6.1.4.1.10106.3.101291.1.1.143
		ham3000c01v1EmbG4p0rMonPh OBJECT-TYPE
			SYNTAX Bit0Nor1Inv
			MAX-ACCESS read-write
			STATUS current
			DESCRIPTION
				"Phase applied to the secundary channel in the stereophonic audio pair for generating the monophonic audio in G4P0R PGM OUT"
		::= { ham3000c01v1Entry 143 }

		-- 1.3.6.1.4.1.10106.3.101291.1.1.145
		ham3000c01v1EmbG4p0rMono OBJECT-TYPE
			SYNTAX BitMask
			MAX-ACCESS read-write
			STATUS current
			DESCRIPTION
				"Monophonic audio generated from the audio pair assigned to G4P0R PGM OUT"
		::= { ham3000c01v1Entry 145 }

		-- 1.3.6.1.4.1.10106.3.101291.1.1.147
		ham3000c01v1EmbG4p1l OBJECT-TYPE
			SYNTAX AudioMxInputA
			MAX-ACCESS read-write
			STATUS current
			DESCRIPTION
				"Audio channel assignment to the audio channel embedded in G4P1L PGM OUT"
		::= { ham3000c01v1Entry 147 }

		-- 1.3.6.1.4.1.10106.3.101291.1.1.149
		ham3000c01v1EmbG4p1lMonPh OBJECT-TYPE
			SYNTAX Bit0Nor1Inv
			MAX-ACCESS read-write
			STATUS current
			DESCRIPTION
				"Phase applied to the secundary channel in the stereophonic audio pair for generating the monophonic audio in G4P1L PGM OUT"
		::= { ham3000c01v1Entry 149 }

		-- 1.3.6.1.4.1.10106.3.101291.1.1.151
		ham3000c01v1EmbG4p1lMono OBJECT-TYPE
			SYNTAX BitMask
			MAX-ACCESS read-write
			STATUS current
			DESCRIPTION
				"Monophonic audio generated from the audio pair assigned to G4P1L PGM OUT"
		::= { ham3000c01v1Entry 151 }

		-- 1.3.6.1.4.1.10106.3.101291.1.1.153
		ham3000c01v1EmbG4p1r OBJECT-TYPE
			SYNTAX AudioMxInputA
			MAX-ACCESS read-write
			STATUS current
			DESCRIPTION
				"Audio channel assignment to the audio channel embedded in G4P1R PGM OUT"
		::= { ham3000c01v1Entry 153 }

		-- 1.3.6.1.4.1.10106.3.101291.1.1.155
		ham3000c01v1EmbG4p1rMonPh OBJECT-TYPE
			SYNTAX Bit0Nor1Inv
			MAX-ACCESS read-write
			STATUS current
			DESCRIPTION
				"Phase applied to the secundary channel in the stereophonic audio pair for generating the monophonic audio in G4P1R PGM OUT"
		::= { ham3000c01v1Entry 155 }

		-- 1.3.6.1.4.1.10106.3.101291.1.1.157
		ham3000c01v1EmbG4p1rMono OBJECT-TYPE
			SYNTAX BitMask
			MAX-ACCESS read-write
			STATUS current
			DESCRIPTION
				"Monophonic audio generated from the audio pair assigned to G4P1R PGM OUT"
		::= { ham3000c01v1Entry 157 }

		-- 1.3.6.1.4.1.10106.3.101291.1.1.159
		ham3000c01v1AesOut1L OBJECT-TYPE
			SYNTAX AudioMxInputA
			MAX-ACCESS read-write
			STATUS current
			DESCRIPTION
				"Audio channel assignment to the digital audio output AES1L OUT"
		::= { ham3000c01v1Entry 159 }

		-- 1.3.6.1.4.1.10106.3.101291.1.1.161
		ham3000c01v1AesOut1lMonPh OBJECT-TYPE
			SYNTAX Bit0Nor1Inv
			MAX-ACCESS read-write
			STATUS current
			DESCRIPTION
				"Phase applied to the secundary channel in the stereophonic audio pair for generating the monophonic audio in AES1L OUT"
		::= { ham3000c01v1Entry 161 }

		-- 1.3.6.1.4.1.10106.3.101291.1.1.163
		ham3000c01v1AesOut1lMono OBJECT-TYPE
			SYNTAX BitMask
			MAX-ACCESS read-write
			STATUS current
			DESCRIPTION
				"Monophonic audio generated from the audio pair assigned to AES1L OUT"
		::= { ham3000c01v1Entry 163 }

		-- 1.3.6.1.4.1.10106.3.101291.1.1.165
		ham3000c01v1AesOut1R OBJECT-TYPE
			SYNTAX AudioMxInputA
			MAX-ACCESS read-write
			STATUS current
			DESCRIPTION
				"Audio channel assignment to the digital audio output AES1R OUT"
		::= { ham3000c01v1Entry 165 }

		-- 1.3.6.1.4.1.10106.3.101291.1.1.167
		ham3000c01v1AesOut1rMonPh OBJECT-TYPE
			SYNTAX Bit0Nor1Inv
			MAX-ACCESS read-write
			STATUS current
			DESCRIPTION
				"Phase applied to the secundary channel in the stereophonic audio pair for generating the monophonic audio in AES1R OUT"
		::= { ham3000c01v1Entry 167 }

		-- 1.3.6.1.4.1.10106.3.101291.1.1.169
		ham3000c01v1AesOut1rMono OBJECT-TYPE
			SYNTAX BitMask
			MAX-ACCESS read-write
			STATUS current
			DESCRIPTION
				"Monophonic audio generated from the audio pair assigned to AES1R OUT"
		::= { ham3000c01v1Entry 169 }

		-- 1.3.6.1.4.1.10106.3.101291.1.1.171
		ham3000c01v1AesOut2L OBJECT-TYPE
			SYNTAX AudioMxInputA
			MAX-ACCESS read-write
			STATUS current
			DESCRIPTION
				"Audio channel assignment to the digital audio output AES2L OUT"
		::= { ham3000c01v1Entry 171 }

		-- 1.3.6.1.4.1.10106.3.101291.1.1.173
		ham3000c01v1AesOut2lMonPh OBJECT-TYPE
			SYNTAX Bit0Nor1Inv
			MAX-ACCESS read-write
			STATUS current
			DESCRIPTION
				"Phase applied to the secundary channel in the stereophonic audio pair for generating the monophonic audio in AES2L OUT"
		::= { ham3000c01v1Entry 173 }

		-- 1.3.6.1.4.1.10106.3.101291.1.1.175
		ham3000c01v1AesOut2lMono OBJECT-TYPE
			SYNTAX BitMask
			MAX-ACCESS read-write
			STATUS current
			DESCRIPTION
				"Monophonic audio generated from the audio pair assigned to AES2L OUT"
		::= { ham3000c01v1Entry 175 }

		-- 1.3.6.1.4.1.10106.3.101291.1.1.177
		ham3000c01v1AesOut2R OBJECT-TYPE
			SYNTAX AudioMxInputA
			MAX-ACCESS read-write
			STATUS current
			DESCRIPTION
				"Audio channel assignment to the digital audio output AES2R OUT"
		::= { ham3000c01v1Entry 177 }

		-- 1.3.6.1.4.1.10106.3.101291.1.1.179
		ham3000c01v1AesOut2rMonPh OBJECT-TYPE
			SYNTAX Bit0Nor1Inv
			MAX-ACCESS read-write
			STATUS current
			DESCRIPTION
				"Phase applied to the secundary channel in the stereophonic audio pair for generating the monophonic audio in AES2R OUT"
		::= { ham3000c01v1Entry 179 }

		-- 1.3.6.1.4.1.10106.3.101291.1.1.181
		ham3000c01v1AesOut2rMono OBJECT-TYPE
			SYNTAX BitMask
			MAX-ACCESS read-write
			STATUS current
			DESCRIPTION
				"Monophonic audio generated from the audio pair assigned to AES2R OUT"
		::= { ham3000c01v1Entry 181 }

		-- 1.3.6.1.4.1.10106.3.101291.1.1.183
		ham3000c01v1GanG1p0l OBJECT-TYPE
			SYNTAX Gain24dbMute
			MAX-ACCESS read-write
			STATUS current
			DESCRIPTION
				"Gain applied to the digital audio channel embedded in G1P0L PGM OUT"
		::= { ham3000c01v1Entry 183 }

		-- 1.3.6.1.4.1.10106.3.101291.1.1.185
		ham3000c01v1PhaseG1p0l OBJECT-TYPE
			SYNTAX Bit0Nor1Inv
			MAX-ACCESS read-write
			STATUS current
			DESCRIPTION
				"Phase gain applied to the digital audio channel embedded in G1P0L PGM OUT"
		::= { ham3000c01v1Entry 185 }

		-- 1.3.6.1.4.1.10106.3.101291.1.1.187
		ham3000c01v1GanG1p0r OBJECT-TYPE
			SYNTAX Gain24dbMute
			MAX-ACCESS read-write
			STATUS current
			DESCRIPTION
				"Gain applied to the digital audio channel embedded in G1P0R PGM OUT"
		::= { ham3000c01v1Entry 187 }

		-- 1.3.6.1.4.1.10106.3.101291.1.1.189
		ham3000c01v1PhaseG1p0r OBJECT-TYPE
			SYNTAX Bit0Nor1Inv
			MAX-ACCESS read-write
			STATUS current
			DESCRIPTION
				"Phase gain applied to the digital audio channel embedded in G1P0R PGM OUT"
		::= { ham3000c01v1Entry 189 }

		-- 1.3.6.1.4.1.10106.3.101291.1.1.191
		ham3000c01v1GanG1p1l OBJECT-TYPE
			SYNTAX Gain24dbMute
			MAX-ACCESS read-write
			STATUS current
			DESCRIPTION
				"Gain applied to the digital audio channel embedded in G1P1L PGM OUT"
		::= { ham3000c01v1Entry 191 }

		-- 1.3.6.1.4.1.10106.3.101291.1.1.193
		ham3000c01v1PhaseG1p1l OBJECT-TYPE
			SYNTAX Bit0Nor1Inv
			MAX-ACCESS read-write
			STATUS current
			DESCRIPTION
				"Phase gain applied to the digital audio channel embedded in G1P1L PGM OUT"
		::= { ham3000c01v1Entry 193 }

		-- 1.3.6.1.4.1.10106.3.101291.1.1.195
		ham3000c01v1GanG1p1r OBJECT-TYPE
			SYNTAX Gain24dbMute
			MAX-ACCESS read-write
			STATUS current
			DESCRIPTION
				"Gain applied to the digital audio channel embedded in G1P1R PGM OUT"
		::= { ham3000c01v1Entry 195 }

		-- 1.3.6.1.4.1.10106.3.101291.1.1.197
		ham3000c01v1PhaseG1p1r OBJECT-TYPE
			SYNTAX Bit0Nor1Inv
			MAX-ACCESS read-write
			STATUS current
			DESCRIPTION
				"Phase gain applied to the digital audio channel embedded in G1P1R PGM OUT"
		::= { ham3000c01v1Entry 197 }

		-- 1.3.6.1.4.1.10106.3.101291.1.1.199
		ham3000c01v1GanG2p0l OBJECT-TYPE
			SYNTAX Gain24dbMute
			MAX-ACCESS read-write
			STATUS current
			DESCRIPTION
				"Gain applied to the digital audio channel embedded in G2P0L PGM OUT"
		::= { ham3000c01v1Entry 199 }

		-- 1.3.6.1.4.1.10106.3.101291.1.1.201
		ham3000c01v1PhaseG2p0l OBJECT-TYPE
			SYNTAX Bit0Nor1Inv
			MAX-ACCESS read-write
			STATUS current
			DESCRIPTION
				"Phase gain applied to the digital audio channel embedded in G2P0L PGM OUT"
		::= { ham3000c01v1Entry 201 }

		-- 1.3.6.1.4.1.10106.3.101291.1.1.203
		ham3000c01v1GanG2p0r OBJECT-TYPE
			SYNTAX Gain24dbMute
			MAX-ACCESS read-write
			STATUS current
			DESCRIPTION
				"Gain applied to the digital audio channel embedded in G2P0R PGM OUT"
		::= { ham3000c01v1Entry 203 }

		-- 1.3.6.1.4.1.10106.3.101291.1.1.205
		ham3000c01v1PhaseG2p0r OBJECT-TYPE
			SYNTAX Bit0Nor1Inv
			MAX-ACCESS read-write
			STATUS current
			DESCRIPTION
				"Phase gain applied to the digital audio channel embedded in G2P0R PGM OUT"
		::= { ham3000c01v1Entry 205 }

		-- 1.3.6.1.4.1.10106.3.101291.1.1.207
		ham3000c01v1GanG2p1l OBJECT-TYPE
			SYNTAX Gain24dbMute
			MAX-ACCESS read-write
			STATUS current
			DESCRIPTION
				"Gain applied to the digital audio channel embedded in G2P1L PGM OUT"
		::= { ham3000c01v1Entry 207 }

		-- 1.3.6.1.4.1.10106.3.101291.1.1.209
		ham3000c01v1PhaseG2p1l OBJECT-TYPE
			SYNTAX Bit0Nor1Inv
			MAX-ACCESS read-write
			STATUS current
			DESCRIPTION
				"Phase gain applied to the digital audio channel embedded in G2P1L PGM OUT"
		::= { ham3000c01v1Entry 209 }

		-- 1.3.6.1.4.1.10106.3.101291.1.1.211
		ham3000c01v1GanG2p1r OBJECT-TYPE
			SYNTAX Gain24dbMute
			MAX-ACCESS read-write
			STATUS current
			DESCRIPTION
				"Gain applied to the digital audio channel embedded in G2P1R PGM OUT"
		::= { ham3000c01v1Entry 211 }

		-- 1.3.6.1.4.1.10106.3.101291.1.1.213
		ham3000c01v1PhaseG2p1r OBJECT-TYPE
			SYNTAX Bit0Nor1Inv
			MAX-ACCESS read-write
			STATUS current
			DESCRIPTION
				"Phase gain applied to the digital audio channel embedded in G2P1R PGM OUT"
		::= { ham3000c01v1Entry 213 }

		-- 1.3.6.1.4.1.10106.3.101291.1.1.215
		ham3000c01v1GanG3p0l OBJECT-TYPE
			SYNTAX Gain24dbMute
			MAX-ACCESS read-write
			STATUS current
			DESCRIPTION
				"Gain applied to the digital audio channel embedded in G3P0L PGM OUT"
		::= { ham3000c01v1Entry 215 }

		-- 1.3.6.1.4.1.10106.3.101291.1.1.217
		ham3000c01v1PhaseG3p0l OBJECT-TYPE
			SYNTAX Bit0Nor1Inv
			MAX-ACCESS read-write
			STATUS current
			DESCRIPTION
				"Phase gain applied to the digital audio channel embedded in G3P0L PGM OUT"
		::= { ham3000c01v1Entry 217 }

		-- 1.3.6.1.4.1.10106.3.101291.1.1.219
		ham3000c01v1GanG3p0r OBJECT-TYPE
			SYNTAX Gain24dbMute
			MAX-ACCESS read-write
			STATUS current
			DESCRIPTION
				"Gain applied to the digital audio channel embedded in G3P0R PGM OUT"
		::= { ham3000c01v1Entry 219 }

		-- 1.3.6.1.4.1.10106.3.101291.1.1.221
		ham3000c01v1PhaseG3p0r OBJECT-TYPE
			SYNTAX Bit0Nor1Inv
			MAX-ACCESS read-write
			STATUS current
			DESCRIPTION
				"Phase gain applied to the digital audio channel embedded in G3P0R PGM OUT"
		::= { ham3000c01v1Entry 221 }

		-- 1.3.6.1.4.1.10106.3.101291.1.1.223
		ham3000c01v1GanG3p1l OBJECT-TYPE
			SYNTAX Gain24dbMute
			MAX-ACCESS read-write
			STATUS current
			DESCRIPTION
				"Gain applied to the digital audio channel embedded in G3P1L PGM OUT"
		::= { ham3000c01v1Entry 223 }

		-- 1.3.6.1.4.1.10106.3.101291.1.1.225
		ham3000c01v1PhaseG3p1l OBJECT-TYPE
			SYNTAX Bit0Nor1Inv
			MAX-ACCESS read-write
			STATUS current
			DESCRIPTION
				"Phase gain applied to the digital audio channel embedded in G3P1L PGM OUT"
		::= { ham3000c01v1Entry 225 }

		-- 1.3.6.1.4.1.10106.3.101291.1.1.227
		ham3000c01v1GanG3p1r OBJECT-TYPE
			SYNTAX Gain24dbMute
			MAX-ACCESS read-write
			STATUS current
			DESCRIPTION
				"Gain applied to the digital audio channel embedded in G3P1R PGM OUT"
		::= { ham3000c01v1Entry 227 }

		-- 1.3.6.1.4.1.10106.3.101291.1.1.229
		ham3000c01v1PhaseG3p1r OBJECT-TYPE
			SYNTAX Bit0Nor1Inv
			MAX-ACCESS read-write
			STATUS current
			DESCRIPTION
				"Phase gain applied to the digital audio channel embedded in G3P1R PGM OUT"
		::= { ham3000c01v1Entry 229 }

		-- 1.3.6.1.4.1.10106.3.101291.1.1.231
		ham3000c01v1GanG4p0l OBJECT-TYPE
			SYNTAX Gain24dbMute
			MAX-ACCESS read-write
			STATUS current
			DESCRIPTION
				"Gain applied to the digital audio channel embedded in G4P0L PGM OUT"
		::= { ham3000c01v1Entry 231 }

		-- 1.3.6.1.4.1.10106.3.101291.1.1.233
		ham3000c01v1PhaseG4p0l OBJECT-TYPE
			SYNTAX Bit0Nor1Inv
			MAX-ACCESS read-write
			STATUS current
			DESCRIPTION
				"Phase gain applied to the digital audio channel embedded in G4P0L PGM OUT"
		::= { ham3000c01v1Entry 233 }

		-- 1.3.6.1.4.1.10106.3.101291.1.1.235
		ham3000c01v1GanG4p0r OBJECT-TYPE
			SYNTAX Gain24dbMute
			MAX-ACCESS read-write
			STATUS current
			DESCRIPTION
				"Gain applied to the digital audio channel embedded in G4P0R PGM OUT"
		::= { ham3000c01v1Entry 235 }

		-- 1.3.6.1.4.1.10106.3.101291.1.1.237
		ham3000c01v1PhaseG4p0r OBJECT-TYPE
			SYNTAX Bit0Nor1Inv
			MAX-ACCESS read-write
			STATUS current
			DESCRIPTION
				"Phase gain applied to the digital audio channel embedded in G4P0R PGM OUT"
		::= { ham3000c01v1Entry 237 }

		-- 1.3.6.1.4.1.10106.3.101291.1.1.239
		ham3000c01v1GanG4p1l OBJECT-TYPE
			SYNTAX Gain24dbMute
			MAX-ACCESS read-write
			STATUS current
			DESCRIPTION
				"Gain applied to the digital audio channel embedded in G4P1L PGM OUT"
		::= { ham3000c01v1Entry 239 }

		-- 1.3.6.1.4.1.10106.3.101291.1.1.241
		ham3000c01v1PhaseG4p1l OBJECT-TYPE
			SYNTAX Bit0Nor1Inv
			MAX-ACCESS read-write
			STATUS current
			DESCRIPTION
				"Phase gain applied to the digital audio channel embedded in G4P1L PGM OUT"
		::= { ham3000c01v1Entry 241 }

		-- 1.3.6.1.4.1.10106.3.101291.1.1.243
		ham3000c01v1GanG4p1r OBJECT-TYPE
			SYNTAX Gain24dbMute
			MAX-ACCESS read-write
			STATUS current
			DESCRIPTION
				"Gain applied to the digital audio channel embedded in G4P1R PGM OUT"
		::= { ham3000c01v1Entry 243 }

		-- 1.3.6.1.4.1.10106.3.101291.1.1.245
		ham3000c01v1PhaseG4p1r OBJECT-TYPE
			SYNTAX Bit0Nor1Inv
			MAX-ACCESS read-write
			STATUS current
			DESCRIPTION
				"Phase gain applied to the digital audio channel embedded in G4P1R PGM OUT"
		::= { ham3000c01v1Entry 245 }

		-- 1.3.6.1.4.1.10106.3.101291.1.1.247
		ham3000c01v1GanAes1l OBJECT-TYPE
			SYNTAX Gain24dbMute
			MAX-ACCESS read-write
			STATUS current
			DESCRIPTION
				"Gain applied to the digital audio channel output AES1L OUT"
		::= { ham3000c01v1Entry 247 }

		-- 1.3.6.1.4.1.10106.3.101291.1.1.249
		ham3000c01v1PhaseAes1l OBJECT-TYPE
			SYNTAX Bit0Nor1Inv
			MAX-ACCESS read-write
			STATUS current
			DESCRIPTION
				"Phase gain applied to the digital audio channel output AES1L OUT"
		::= { ham3000c01v1Entry 249 }

		-- 1.3.6.1.4.1.10106.3.101291.1.1.251
		ham3000c01v1GanAes1r OBJECT-TYPE
			SYNTAX Gain24dbMute
			MAX-ACCESS read-write
			STATUS current
			DESCRIPTION
				"Gain applied to the digital audio channel output AES1R OUT"
		::= { ham3000c01v1Entry 251 }

		-- 1.3.6.1.4.1.10106.3.101291.1.1.253
		ham3000c01v1PhaseAes1r OBJECT-TYPE
			SYNTAX Bit0Nor1Inv
			MAX-ACCESS read-write
			STATUS current
			DESCRIPTION
				"Phase gain applied to the digital audio channel output AES1R OUT"
		::= { ham3000c01v1Entry 253 }

		-- 1.3.6.1.4.1.10106.3.101291.1.1.255
		ham3000c01v1GanAes2l OBJECT-TYPE
			SYNTAX Gain24dbMute
			MAX-ACCESS read-write
			STATUS current
			DESCRIPTION
				"Gain applied to the digital audio channel output AES2L OUT"
		::= { ham3000c01v1Entry 255 }

		-- 1.3.6.1.4.1.10106.3.101291.1.1.257
		ham3000c01v1PhaseAes2l OBJECT-TYPE
			SYNTAX Bit0Nor1Inv
			MAX-ACCESS read-write
			STATUS current
			DESCRIPTION
				"Phase gain applied to the digital audio channel output AES2L OUT"
		::= { ham3000c01v1Entry 257 }

		-- 1.3.6.1.4.1.10106.3.101291.1.1.259
		ham3000c01v1GanAes2r OBJECT-TYPE
			SYNTAX Gain24dbMute
			MAX-ACCESS read-write
			STATUS current
			DESCRIPTION
				"Gain applied to the digital audio channel output AES2R OUT"
		::= { ham3000c01v1Entry 259 }

		-- 1.3.6.1.4.1.10106.3.101291.1.1.261
		ham3000c01v1PhaseAes2r OBJECT-TYPE
			SYNTAX Bit0Nor1Inv
			MAX-ACCESS read-write
			STATUS current
			DESCRIPTION
				"Phase gain applied to the digital audio channel output AES2R OUT"
		::= { ham3000c01v1Entry 261 }

		-- 1.3.6.1.4.1.10106.3.101291.1.1.263
		ham3000c01v1DelayG1p0l OBJECT-TYPE
			SYNTAX DelayAud
			MAX-ACCESS read-write
			STATUS current
			DESCRIPTION
				"Audio delay in the audio channel embedded in G1P0L PGM OUT"
		::= { ham3000c01v1Entry 263 }

		-- 1.3.6.1.4.1.10106.3.101291.1.1.265
		ham3000c01v1DelayG1p0r OBJECT-TYPE
			SYNTAX DelayAud
			MAX-ACCESS read-write
			STATUS current
			DESCRIPTION
				"Audio delay in the audio channel embedded in G1P0R PGM OUT"
		::= { ham3000c01v1Entry 265 }

		-- 1.3.6.1.4.1.10106.3.101291.1.1.267
		ham3000c01v1DelayG1p1l OBJECT-TYPE
			SYNTAX DelayAud
			MAX-ACCESS read-write
			STATUS current
			DESCRIPTION
				"Audio delay in the audio channel embedded in G1P1L PGM OUT"
		::= { ham3000c01v1Entry 267 }

		-- 1.3.6.1.4.1.10106.3.101291.1.1.269
		ham3000c01v1DelayG1p1r OBJECT-TYPE
			SYNTAX DelayAud
			MAX-ACCESS read-write
			STATUS current
			DESCRIPTION
				"Audio delay in the audio channel embedded in G1P1R PGM OUT"
		::= { ham3000c01v1Entry 269 }

		-- 1.3.6.1.4.1.10106.3.101291.1.1.271
		ham3000c01v1DelayG2p0l OBJECT-TYPE
			SYNTAX DelayAud
			MAX-ACCESS read-write
			STATUS current
			DESCRIPTION
				"Audio delay in the audio channel embedded in G2P0L PGM OUT"
		::= { ham3000c01v1Entry 271 }

		-- 1.3.6.1.4.1.10106.3.101291.1.1.273
		ham3000c01v1DelayG2p0r OBJECT-TYPE
			SYNTAX DelayAud
			MAX-ACCESS read-write
			STATUS current
			DESCRIPTION
				"Audio delay in the audio channel embedded in G2P1R PGM OUT"
		::= { ham3000c01v1Entry 273 }

		-- 1.3.6.1.4.1.10106.3.101291.1.1.275
		ham3000c01v1DelayG2p1l OBJECT-TYPE
			SYNTAX DelayAud
			MAX-ACCESS read-write
			STATUS current
			DESCRIPTION
				"Audio delay in the audio channel embedded in G2P1L PGM OUT"
		::= { ham3000c01v1Entry 275 }

		-- 1.3.6.1.4.1.10106.3.101291.1.1.277
		ham3000c01v1DelayG2p1r OBJECT-TYPE
			SYNTAX DelayAud
			MAX-ACCESS read-write
			STATUS current
			DESCRIPTION
				"Audio delay in the audio channel embedded in G2P1R PGM OUT"
		::= { ham3000c01v1Entry 277 }

		-- 1.3.6.1.4.1.10106.3.101291.1.1.279
		ham3000c01v1DelayG3p0l OBJECT-TYPE
			SYNTAX DelayAud
			MAX-ACCESS read-write
			STATUS current
			DESCRIPTION
				"Audio delay in the audio channel embedded in G3P0L PGM OUT"
		::= { ham3000c01v1Entry 279 }

		-- 1.3.6.1.4.1.10106.3.101291.1.1.281
		ham3000c01v1DelayG3p0r OBJECT-TYPE
			SYNTAX DelayAud
			MAX-ACCESS read-write
			STATUS current
			DESCRIPTION
				"Audio delay in the audio channel embedded in G3P0R PGM OUT"
		::= { ham3000c01v1Entry 281 }

		-- 1.3.6.1.4.1.10106.3.101291.1.1.283
		ham3000c01v1DelayG3p1l OBJECT-TYPE
			SYNTAX DelayAud
			MAX-ACCESS read-write
			STATUS current
			DESCRIPTION
				"Audio delay in the audio channel embedded in G3P1L PGM OUT"
		::= { ham3000c01v1Entry 283 }

		-- 1.3.6.1.4.1.10106.3.101291.1.1.285
		ham3000c01v1DelayG3p1r OBJECT-TYPE
			SYNTAX DelayAud
			MAX-ACCESS read-write
			STATUS current
			DESCRIPTION
				"Audio delay in the audio channel embedded in G3P1R PGM OUT"
		::= { ham3000c01v1Entry 285 }

		-- 1.3.6.1.4.1.10106.3.101291.1.1.287
		ham3000c01v1DelayG4p0l OBJECT-TYPE
			SYNTAX DelayAud
			MAX-ACCESS read-write
			STATUS current
			DESCRIPTION
				"Audio delay in the audio channel embedded in G4P0L PGM OUT"
		::= { ham3000c01v1Entry 287 }

		-- 1.3.6.1.4.1.10106.3.101291.1.1.289
		ham3000c01v1DelayG4p0r OBJECT-TYPE
			SYNTAX DelayAud
			MAX-ACCESS read-write
			STATUS current
			DESCRIPTION
				"Audio delay in the audio channel embedded in G4P0R PGM OUT"
		::= { ham3000c01v1Entry 289 }

		-- 1.3.6.1.4.1.10106.3.101291.1.1.291
		ham3000c01v1DelayG4p1l OBJECT-TYPE
			SYNTAX DelayAud
			MAX-ACCESS read-write
			STATUS current
			DESCRIPTION
				"Audio delay in the audio channel embedded in G4P1L PGM OUT"
		::= { ham3000c01v1Entry 291 }

		-- 1.3.6.1.4.1.10106.3.101291.1.1.293
		ham3000c01v1DelayG4p1r OBJECT-TYPE
			SYNTAX DelayAud
			MAX-ACCESS read-write
			STATUS current
			DESCRIPTION
				"Audio delay in the audio channel embedded in G4P1R PGM OUT"
		::= { ham3000c01v1Entry 293 }

		-- 1.3.6.1.4.1.10106.3.101291.1.1.295
		ham3000c01v1DelayAes1l OBJECT-TYPE
			SYNTAX DelayAud
			MAX-ACCESS read-write
			STATUS current
			DESCRIPTION
				"Audio delay in the digital audio channel AES1L OUT"
		::= { ham3000c01v1Entry 295 }

		-- 1.3.6.1.4.1.10106.3.101291.1.1.297
		ham3000c01v1DelayAes1r OBJECT-TYPE
			SYNTAX DelayAud
			MAX-ACCESS read-write
			STATUS current
			DESCRIPTION
				"Audio delay in the digital audio channel AES1R OUT"
		::= { ham3000c01v1Entry 297 }

		-- 1.3.6.1.4.1.10106.3.101291.1.1.299
		ham3000c01v1DelayAes2l OBJECT-TYPE
			SYNTAX DelayAud
			MAX-ACCESS read-write
			STATUS current
			DESCRIPTION
				"Audio delay in the digital audio channel AES2L OUT"
		::= { ham3000c01v1Entry 299 }

		-- 1.3.6.1.4.1.10106.3.101291.1.1.301
		ham3000c01v1DelayAes2r OBJECT-TYPE
			SYNTAX DelayAud
			MAX-ACCESS read-write
			STATUS current
			DESCRIPTION
				"Audio delay in the digital audio channel AES2R OUT"
		::= { ham3000c01v1Entry 301 }

		-- 1.3.6.1.4.1.10106.3.101291.1.1.303
		ham3000c01v1StatFlash OBJECT-TYPE
			SYNTAX BitFailN
			MAX-ACCESS read-only
			STATUS current
			DESCRIPTION
				"Displays the Flash state"
		::= { ham3000c01v1Entry 303 }

		-- 1.3.6.1.4.1.10106.3.101291.1.1.305
		ham3000c01v1NoSignalMain OBJECT-TYPE
			SYNTAX BitFail
			MAX-ACCESS read-only
			STATUS current
			DESCRIPTION
				"There is no SDI signal or the format is not supported in PGM IN"
		::= { ham3000c01v1Entry 305 }

		-- 1.3.6.1.4.1.10106.3.101291.1.1.306
		ham3000c01v1NoSignalMainTrapEnable OBJECT-TYPE
			SYNTAX AlarmEnable
			MAX-ACCESS read-write
			STATUS current
			DESCRIPTION
				"There is no SDI signal or the format is not supported in PGM IN Trap Enable"
		::= { ham3000c01v1Entry 306 }

		-- 1.3.6.1.4.1.10106.3.101291.1.1.307
		ham3000c01v1UnlockMain OBJECT-TYPE
			SYNTAX BitFail
			MAX-ACCESS read-only
			STATUS current
			DESCRIPTION
				"Indicates signal unlock fail"
		::= { ham3000c01v1Entry 307 }

		-- 1.3.6.1.4.1.10106.3.101291.1.1.308
		ham3000c01v1UnlockMainTrapEnable OBJECT-TYPE
			SYNTAX AlarmEnable
			MAX-ACCESS read-write
			STATUS current
			DESCRIPTION
				"Indicates signal unlock fail Trap Enable"
		::= { ham3000c01v1Entry 308 }

		-- 1.3.6.1.4.1.10106.3.101291.1.1.309
		ham3000c01v1EdhErrorMain OBJECT-TYPE
			SYNTAX BitFail
			MAX-ACCESS read-only
			STATUS current
			DESCRIPTION
				"There are EDH/CRC errors on PGM IN"
		::= { ham3000c01v1Entry 309 }

		-- 1.3.6.1.4.1.10106.3.101291.1.1.310
		ham3000c01v1EdhErrorMainTrapEnable OBJECT-TYPE
			SYNTAX AlarmEnable
			MAX-ACCESS read-write
			STATUS current
			DESCRIPTION
				"There are EDH/CRC errors on PGM IN Trap Enable"
		::= { ham3000c01v1Entry 310 }

		-- 1.3.6.1.4.1.10106.3.101291.1.1.311
		ham3000c01v1NoSignalAux OBJECT-TYPE
			SYNTAX BitFail
			MAX-ACCESS read-only
			STATUS current
			DESCRIPTION
				"There is no SDI signal or the format is not supported in AUX IN"
		::= { ham3000c01v1Entry 311 }

		-- 1.3.6.1.4.1.10106.3.101291.1.1.313
		ham3000c01v1UnlockAux OBJECT-TYPE
			SYNTAX BitFail
			MAX-ACCESS read-only
			STATUS current
			DESCRIPTION
				"Indicates signal AUX IN unlock fail"
		::= { ham3000c01v1Entry 313 }

		-- 1.3.6.1.4.1.10106.3.101291.1.1.315
		ham3000c01v1EdhErrorAux OBJECT-TYPE
			SYNTAX BitFail
			MAX-ACCESS read-only
			STATUS current
			DESCRIPTION
				"There are EDH/CRC errors on AUX IN signal"
		::= { ham3000c01v1Entry 315 }

		-- 1.3.6.1.4.1.10106.3.101291.1.1.317
		ham3000c01v1RefAbsent OBJECT-TYPE
			SYNTAX BitFail
			MAX-ACCESS read-only
			STATUS current
			DESCRIPTION
				"There is no reference signal"
		::= { ham3000c01v1Entry 317 }

		-- 1.3.6.1.4.1.10106.3.101291.1.1.318
		ham3000c01v1RefAbsentTrapEnable OBJECT-TYPE
			SYNTAX AlarmEnable
			MAX-ACCESS read-write
			STATUS current
			DESCRIPTION
				"There is no reference signal Trap Enable"
		::= { ham3000c01v1Entry 318 }

		-- 1.3.6.1.4.1.10106.3.101291.1.1.319
		ham3000c01v1RefUnlock OBJECT-TYPE
			SYNTAX BitFail
			MAX-ACCESS read-only
			STATUS current
			DESCRIPTION
				"Reference input unlock fail"
		::= { ham3000c01v1Entry 319 }

		-- 1.3.6.1.4.1.10106.3.101291.1.1.320
		ham3000c01v1RefUnlockTrapEnable OBJECT-TYPE
			SYNTAX AlarmEnable
			MAX-ACCESS read-write
			STATUS current
			DESCRIPTION
				"Reference input unlock fail Trap Enable"
		::= { ham3000c01v1Entry 320 }

		-- 1.3.6.1.4.1.10106.3.101291.1.1.321
		ham3000c01v1FormatMainIn OBJECT-TYPE
			SYNTAX SdiHd3gFmt3
			MAX-ACCESS read-only
			STATUS current
			DESCRIPTION
				"Indicates the SDI received signal format"
		::= { ham3000c01v1Entry 321 }

		-- 1.3.6.1.4.1.10106.3.101291.1.1.323
		ham3000c01v1FormatAuxIn OBJECT-TYPE
			SYNTAX SdiHd3gFmt3
			MAX-ACCESS read-only
			STATUS current
			DESCRIPTION
				"Indicates the SDI_AUX received signal format"
		::= { ham3000c01v1Entry 323 }

		-- 1.3.6.1.4.1.10106.3.101291.1.1.325
		ham3000c01v1FormatRef OBJECT-TYPE
			SYNTAX SdiHd3gFmt3
			MAX-ACCESS read-only
			STATUS current
			DESCRIPTION
				"Indicates the input reference signal format"
		::= { ham3000c01v1Entry 325 }

		-- 1.3.6.1.4.1.10106.3.101291.1.1.327
		ham3000c01v1FormatMainTx OBJECT-TYPE
			SYNTAX SdiHd3gFmt3
			MAX-ACCESS read-only
			STATUS current
			DESCRIPTION
				"Indicates the SDI transmited signal format"
		::= { ham3000c01v1Entry 327 }

		-- 1.3.6.1.4.1.10106.3.101291.1.1.329
		ham3000c01v1SigDelay OBJECT-TYPE
			SYNTAX DelayX20Us
			MAX-ACCESS read-only
			STATUS current
			DESCRIPTION
				"Indicates the input to output delay"
		::= { ham3000c01v1Entry 329 }

		-- 1.3.6.1.4.1.10106.3.101291.1.1.331
		ham3000c01v1Gr1MainPres OBJECT-TYPE
			SYNTAX Bit0No1Yes
			MAX-ACCESS read-only
			STATUS current
			DESCRIPTION
				"Indicates group 1 presence in PGM IN"
		::= { ham3000c01v1Entry 331 }

		-- 1.3.6.1.4.1.10106.3.101291.1.1.332
		ham3000c01v1Gr1MainPresTrapEnable OBJECT-TYPE
			SYNTAX AlarmEnable
			MAX-ACCESS read-write
			STATUS current
			DESCRIPTION
				"Indicates group 1 presence in PGM IN Trap Enable"
		::= { ham3000c01v1Entry 332 }

		-- 1.3.6.1.4.1.10106.3.101291.1.1.333
		ham3000c01v1Gr2MainPres OBJECT-TYPE
			SYNTAX Bit0No1Yes
			MAX-ACCESS read-only
			STATUS current
			DESCRIPTION
				"Indicates group 2 presence in PGM IN"
		::= { ham3000c01v1Entry 333 }

		-- 1.3.6.1.4.1.10106.3.101291.1.1.334
		ham3000c01v1Gr2MainPresTrapEnable OBJECT-TYPE
			SYNTAX AlarmEnable
			MAX-ACCESS read-write
			STATUS current
			DESCRIPTION
				"Indicates group 2 presence in PGM IN Trap Enable"
		::= { ham3000c01v1Entry 334 }

		-- 1.3.6.1.4.1.10106.3.101291.1.1.335
		ham3000c01v1Gr3MainPres OBJECT-TYPE
			SYNTAX Bit0No1Yes
			MAX-ACCESS read-only
			STATUS current
			DESCRIPTION
				"Indicates group 3 presence in PGM IN"
		::= { ham3000c01v1Entry 335 }

		-- 1.3.6.1.4.1.10106.3.101291.1.1.336
		ham3000c01v1Gr3MainPresTrapEnable OBJECT-TYPE
			SYNTAX AlarmEnable
			MAX-ACCESS read-write
			STATUS current
			DESCRIPTION
				"Indicates group 3 presence in PGM IN Trap Enable"
		::= { ham3000c01v1Entry 336 }

		-- 1.3.6.1.4.1.10106.3.101291.1.1.337
		ham3000c01v1Gr4MainPres OBJECT-TYPE
			SYNTAX Bit0No1Yes
			MAX-ACCESS read-only
			STATUS current
			DESCRIPTION
				"Indicates group 4 presence in PGM IN"
		::= { ham3000c01v1Entry 337 }

		-- 1.3.6.1.4.1.10106.3.101291.1.1.338
		ham3000c01v1Gr4MainPresTrapEnable OBJECT-TYPE
			SYNTAX AlarmEnable
			MAX-ACCESS read-write
			STATUS current
			DESCRIPTION
				"Indicates group 4 presence in PGM IN Trap Enable"
		::= { ham3000c01v1Entry 338 }

		-- 1.3.6.1.4.1.10106.3.101291.1.1.339
		ham3000c01v1Gr1AuxPres OBJECT-TYPE
			SYNTAX Bit0No1Yes
			MAX-ACCESS read-only
			STATUS current
			DESCRIPTION
				"Indicates group 1 presence in AUX IN"
		::= { ham3000c01v1Entry 339 }

		-- 1.3.6.1.4.1.10106.3.101291.1.1.341
		ham3000c01v1Gr2AuxPres OBJECT-TYPE
			SYNTAX Bit0No1Yes
			MAX-ACCESS read-only
			STATUS current
			DESCRIPTION
				"Indicates group 2 presence in AUX IN"
		::= { ham3000c01v1Entry 341 }

		-- 1.3.6.1.4.1.10106.3.101291.1.1.343
		ham3000c01v1Gr3AuxPres OBJECT-TYPE
			SYNTAX Bit0No1Yes
			MAX-ACCESS read-only
			STATUS current
			DESCRIPTION
				"Indicates group 3 presence in AUX IN"
		::= { ham3000c01v1Entry 343 }

		-- 1.3.6.1.4.1.10106.3.101291.1.1.345
		ham3000c01v1Gr4AuxPres OBJECT-TYPE
			SYNTAX Bit0No1Yes
			MAX-ACCESS read-only
			STATUS current
			DESCRIPTION
				"Indicates group 4 presence in AUX IN"
		::= { ham3000c01v1Entry 345 }

		-- 1.3.6.1.4.1.10106.3.101291.1.1.347
		ham3000c01v1Aes1Ok OBJECT-TYPE
			SYNTAX BitFailN
			MAX-ACCESS read-only
			STATUS current
			DESCRIPTION
				"Indicates frame validity of input AES1"
		::= { ham3000c01v1Entry 347 }

		-- 1.3.6.1.4.1.10106.3.101291.1.1.349
		ham3000c01v1Aes1Frq OBJECT-TYPE
			SYNTAX AudioSelFreq6
			MAX-ACCESS read-only
			STATUS current
			DESCRIPTION
				"Indicates sampling frequency of the AES1 input"
		::= { ham3000c01v1Entry 349 }

		-- 1.3.6.1.4.1.10106.3.101291.1.1.351
		ham3000c01v1Aes2Ok OBJECT-TYPE
			SYNTAX BitFailN
			MAX-ACCESS read-only
			STATUS current
			DESCRIPTION
				"Indicates frame validity of input AES2"
		::= { ham3000c01v1Entry 351 }

		-- 1.3.6.1.4.1.10106.3.101291.1.1.353
		ham3000c01v1Aes2Frq OBJECT-TYPE
			SYNTAX AudioSelFreq6
			MAX-ACCESS read-only
			STATUS current
			DESCRIPTION
				"Indicates sampling frequency of the AES2 input"
		::= { ham3000c01v1Entry 353 }

		-- 1.3.6.1.4.1.10106.3.101291.1.1.355
		ham3000c01v1AudStatMain OBJECT-TYPE
			SYNTAX BitFail
			MAX-ACCESS read-only
			STATUS current
			DESCRIPTION
				"Indicates audio fail in audio channels embedded in PGM IN"
		::= { ham3000c01v1Entry 355 }

		-- 1.3.6.1.4.1.10106.3.101291.1.1.356
		ham3000c01v1AudStatMainTrapEnable OBJECT-TYPE
			SYNTAX AlarmEnable
			MAX-ACCESS read-write
			STATUS current
			DESCRIPTION
				"Indicates audio fail in audio channels embedded in PGM IN Trap Enable"
		::= { ham3000c01v1Entry 356 }

		-- 1.3.6.1.4.1.10106.3.101291.1.1.357
		ham3000c01v1AudStatAux OBJECT-TYPE
			SYNTAX BitFail
			MAX-ACCESS read-only
			STATUS current
			DESCRIPTION
				"Indicates audio fail in audio channels embedded in AUX IN"
		::= { ham3000c01v1Entry 357 }

		-- 1.3.6.1.4.1.10106.3.101291.1.1.358
		ham3000c01v1AudStatAuxTrapEnable OBJECT-TYPE
			SYNTAX AlarmEnable
			MAX-ACCESS read-write
			STATUS current
			DESCRIPTION
				"Indicates audio fail in audio channels embedded in AUX IN Trap Enable"
		::= { ham3000c01v1Entry 358 }

		-- 1.3.6.1.4.1.10106.3.101291.1.1.359
		ham3000c01v1AudStatAes1 OBJECT-TYPE
			SYNTAX BitFail
			MAX-ACCESS read-only
			STATUS current
			DESCRIPTION
				"Indicates audio fail in AES1 input"
		::= { ham3000c01v1Entry 359 }

		-- 1.3.6.1.4.1.10106.3.101291.1.1.360
		ham3000c01v1AudStatAes1TrapEnable OBJECT-TYPE
			SYNTAX AlarmEnable
			MAX-ACCESS read-write
			STATUS current
			DESCRIPTION
				"Indicates audio fail in AES1 input Trap Enable"
		::= { ham3000c01v1Entry 360 }

		-- 1.3.6.1.4.1.10106.3.101291.1.1.361
		ham3000c01v1AudStatAes2 OBJECT-TYPE
			SYNTAX BitFail
			MAX-ACCESS read-only
			STATUS current
			DESCRIPTION
				"Indicates audio fail in AES2 input"
		::= { ham3000c01v1Entry 361 }

		-- 1.3.6.1.4.1.10106.3.101291.1.1.362
		ham3000c01v1AudStatAes2TrapEnable OBJECT-TYPE
			SYNTAX AlarmEnable
			MAX-ACCESS read-write
			STATUS current
			DESCRIPTION
				"Indicates audio fail in AES2 input Trap Enable"
		::= { ham3000c01v1Entry 362 }

		-- 1.3.6.1.4.1.10106.3.101291.1.1.363
		ham3000c01v1OvldPgmOut OBJECT-TYPE
			SYNTAX BitFail
			MAX-ACCESS read-only
			STATUS current
			DESCRIPTION
				"Indicates audio overload in SDI output PGM OUT"
		::= { ham3000c01v1Entry 363 }

		-- 1.3.6.1.4.1.10106.3.101291.1.1.364
		ham3000c01v1OvldPgmOutTrapEnable OBJECT-TYPE
			SYNTAX AlarmEnable
			MAX-ACCESS read-write
			STATUS current
			DESCRIPTION
				"Indicates audio overload in SDI output PGM OUT Trap Enable"
		::= { ham3000c01v1Entry 364 }

		-- 1.3.6.1.4.1.10106.3.101291.1.1.365
		ham3000c01v1OvldAes1Out OBJECT-TYPE
			SYNTAX BitFail
			MAX-ACCESS read-only
			STATUS current
			DESCRIPTION
				"Indicates audio overload in AES1 OUT"
		::= { ham3000c01v1Entry 365 }

		-- 1.3.6.1.4.1.10106.3.101291.1.1.366
		ham3000c01v1OvldAes1OutTrapEnable OBJECT-TYPE
			SYNTAX AlarmEnable
			MAX-ACCESS read-write
			STATUS current
			DESCRIPTION
				"Indicates audio overload in AES1 OUT Trap Enable"
		::= { ham3000c01v1Entry 366 }

		-- 1.3.6.1.4.1.10106.3.101291.1.1.367
		ham3000c01v1OvldAes2Out OBJECT-TYPE
			SYNTAX BitFail
			MAX-ACCESS read-only
			STATUS current
			DESCRIPTION
				"Indicates audio overload in AES2 OUT"
		::= { ham3000c01v1Entry 367 }

		-- 1.3.6.1.4.1.10106.3.101291.1.1.368
		ham3000c01v1OvldAes2OutTrapEnable OBJECT-TYPE
			SYNTAX AlarmEnable
			MAX-ACCESS read-write
			STATUS current
			DESCRIPTION
				"Indicates audio overload in AES2 OUT Trap Enable"
		::= { ham3000c01v1Entry 368 }

		-- 1.3.6.1.4.1.10106.3.101291.1.1.369
		ham3000c01v1SilPgmOut OBJECT-TYPE
			SYNTAX BitFail
			MAX-ACCESS read-only
			STATUS current
			DESCRIPTION
				"Indicates audio silence in SDI_PGM_OUT"
		::= { ham3000c01v1Entry 369 }

		-- 1.3.6.1.4.1.10106.3.101291.1.1.370
		ham3000c01v1SilPgmOutTrapEnable OBJECT-TYPE
			SYNTAX AlarmEnable
			MAX-ACCESS read-write
			STATUS current
			DESCRIPTION
				"Indicates audio silence in SDI_PGM_OUT Trap Enable"
		::= { ham3000c01v1Entry 370 }

		-- 1.3.6.1.4.1.10106.3.101291.1.1.371
		ham3000c01v1SilAes1Out OBJECT-TYPE
			SYNTAX BitFail
			MAX-ACCESS read-only
			STATUS current
			DESCRIPTION
				"Indicates audio silence in AES1_OUT"
		::= { ham3000c01v1Entry 371 }

		-- 1.3.6.1.4.1.10106.3.101291.1.1.372
		ham3000c01v1SilAes1OutTrapEnable OBJECT-TYPE
			SYNTAX AlarmEnable
			MAX-ACCESS read-write
			STATUS current
			DESCRIPTION
				"Indicates audio silence in AES1_OUT Trap Enable"
		::= { ham3000c01v1Entry 372 }

		-- 1.3.6.1.4.1.10106.3.101291.1.1.373
		ham3000c01v1SilAes2Out OBJECT-TYPE
			SYNTAX BitFail
			MAX-ACCESS read-only
			STATUS current
			DESCRIPTION
				"Indicates audio silence in AES2_OUT"
		::= { ham3000c01v1Entry 373 }

		-- 1.3.6.1.4.1.10106.3.101291.1.1.374
		ham3000c01v1SilAes2OutTrapEnable OBJECT-TYPE
			SYNTAX AlarmEnable
			MAX-ACCESS read-write
			STATUS current
			DESCRIPTION
				"Indicates audio silence in AES2_OUT Trap Enable"
		::= { ham3000c01v1Entry 374 }

		-- 1.3.6.1.4.1.10106.3.101291.1.1.375
		ham3000c01v1SerialNo OBJECT-TYPE
			SYNTAX SerialNo
			MAX-ACCESS read-only
			STATUS current
			DESCRIPTION
				"Serial number"
		::= { ham3000c01v1Entry 375 }

		-- 1.3.6.1.4.1.10106.3.101291.1.1.377
		ham3000c01v1SavePreset OBJECT-TYPE
			SYNTAX Preset16Save
			MAX-ACCESS read-write
			STATUS current
			DESCRIPTION
				"Allows saving a preset"
		::= { ham3000c01v1Entry 377 }

		-- 1.3.6.1.4.1.10106.3.101291.1.1.379
		ham3000c01v1VidAuxSel OBJECT-TYPE
			SYNTAX Bit0Aux1Pgm
			MAX-ACCESS read-write
			STATUS current
			DESCRIPTION
				"Allows selecting the auxiliar input beetween the AUX IN and the PGM IN"
		::= { ham3000c01v1Entry 379 }

		-- 1.3.6.1.4.1.10106.3.404701
		agw3000c01v1 OBJECT IDENTIFIER ::= { albalaProducts 404701 }

		-- 1.3.6.1.4.1.10106.3.404701.1
		agw3000c01v1Table  OBJECT-TYPE
			SYNTAX SEQUENCE OF Agw3000c01v1Entry
			MAX-ACCESS not-accessible
			STATUS current
			DESCRIPTION
				"Module  AGW3000C01V1 Table"
			::= { agw3000c01v1 1 }

		-- 1.3.6.1.4.1.10106.3.404701.1.1
		agw3000c01v1Entry  OBJECT-TYPE
			SYNTAX Agw3000c01v1Entry
			MAX-ACCESS not-accessible
			STATUS current
			DESCRIPTION
				"Module AGW3000C01V1 Entry"
			INDEX { agw3000c01v1Index }
			::= { agw3000c01v1Table 1 }

			Agw3000c01v1Entry ::=
			SEQUENCE {
				agw3000c01v1Index
				ModuleIndex,
				agw3000c01v1Mode
				ChgOverMode2,
				agw3000c01v1ModeTrapEnable
				AlarmEnable,
				agw3000c01v1DvbTMode
				Bit0No1Yes,
				agw3000c01v1DvbTModeTrapEnable
				AlarmEnable,
				agw3000c01v1NullPckRtp
				Bit0No1Yes,
				agw3000c01v1NarrowPllBw
				Bit0No1Yes,
				agw3000c01v1Buzzer
				BitMask,
				agw3000c01v1GpioMode
				GpioMode,
				agw3000c01v1InputStChange
				Bit0No1Yes,
				agw3000c01v1InputChange
				Bit0No1Yes,
				agw3000c01v1EnaAsi1
				BitMask,
				agw3000c01v1EnaAsi2
				BitMask,
				agw3000c01v1EnaIp1
				BitMask,
				agw3000c01v1EnaIp2
				BitMask,
				agw3000c01v1AsiOut1In
				GatewayInput3,
				agw3000c01v1AsiOut1InTrapEnable
				AlarmEnable,
				agw3000c01v1AsiOut2In
				GatewayInput3,
				agw3000c01v1AsiOut2InTrapEnable
				AlarmEnable,
				agw3000c01v1IpOut1In
				GatewayInput3,
				agw3000c01v1IpOut1InTrapEnable
				AlarmEnable,
				agw3000c01v1IpOut2In
				GatewayInput3,
				agw3000c01v1IpOut2InTrapEnable
				AlarmEnable,
				agw3000c01v1PingEnable1
				Bit0No1Yes,
				agw3000c01v1PingEnable2
				Bit0No1Yes,
				agw3000c01v1IpLinkFailEn
				Bit0No1Yes,
				agw3000c01v1IpDestFailEn
				Bit0No1Yes,
				agw3000c01v1MaxTimeOut
				TimeX1Ms1,
				agw3000c01v1StatReset
				Bit0No1Yes,
				agw3000c01v1StatSel
				Bit0Ipm1Ipr,
				agw3000c01v1StatMode
				Bit01s1Total,
				agw3000c01v1IgmpVersion
				Bit0V21V3,
				agw3000c01v1EthMode
				EthMode,
				agw3000c01v1PckDelAsiIn1
				DelayPacket1,
				agw3000c01v1PckDelAsiIn2
				DelayPacket1,
				agw3000c01v1PckDelIpIn1
				DelayPacket1,
				agw3000c01v1PckDelIpIn2
				DelayPacket1,
				agw3000c01v1AsiIn1Prior0
				Uint2,
				agw3000c01v1AsiIn2Prior0
				Uint2,
				agw3000c01v1IpIn1Prior0
				Uint2,
				agw3000c01v1IpIn2Prior0
				Uint2,
				agw3000c01v1AsiIn1Prior1
				Uint2,
				agw3000c01v1AsiIn2Prior1
				Uint2,
				agw3000c01v1IpIn1Prior1
				Uint2,
				agw3000c01v1IpIn2Prior1
				Uint2,
				agw3000c01v1AsiIn1Prior2
				Uint2,
				agw3000c01v1AsiIn2Prior2
				Uint2,
				agw3000c01v1IpIn1Prior2
				Uint2,
				agw3000c01v1IpIn2Prior2
				Uint2,
				agw3000c01v1AsiIn1Prior3
				Uint2,
				agw3000c01v1AsiIn2Prior3
				Uint2,
				agw3000c01v1IpIn1Prior3
				Uint2,
				agw3000c01v1IpIn2Prior3
				Uint2,
				agw3000c01v1ActivePreset
				Preset16Active,
				agw3000c01v1LoadPreset
				Preset16Load,
				agw3000c01v1SavePreset
				Preset16Save,
				agw3000c01v1Str1UipDAdd3
				Uint8,
				agw3000c01v1Str1UipDAdd2
				Uint8,
				agw3000c01v1Str1UipDAdd1
				Uint8,
				agw3000c01v1Str1UipDAdd0
				Uint8,
				agw3000c01v1Str1MipDAdd3
				Uint8,
				agw3000c01v1Str1MipDAdd2
				Uint8,
				agw3000c01v1Str1MipDAdd1
				Uint8,
				agw3000c01v1Str1MipDAdd0
				Uint8,
				agw3000c01v1Str1DPort
				Uint16,
				agw3000c01v1Str1FecEna
				Bit0No1Yes,
				agw3000c01v1Str1MulticEna
				IpaTxMode,
				agw3000c01v1VlanRx1Enable
				Bit0No1Yes,
				agw3000c01v1VlanRx1Id
				Uint12,
				agw3000c01v1Str2UipDAdd3
				Uint8,
				agw3000c01v1Str2UipDAdd2
				Uint8,
				agw3000c01v1Str2UipDAdd1
				Uint8,
				agw3000c01v1Str2UipDAdd0
				Uint8,
				agw3000c01v1Str2MipDAdd3
				Uint8,
				agw3000c01v1Str2MipDAdd2
				Uint8,
				agw3000c01v1Str2MipDAdd1
				Uint8,
				agw3000c01v1Str2MipDAdd0
				Uint8,
				agw3000c01v1Str2DPort
				Uint16,
				agw3000c01v1Str2FecEna
				Bit0No1Yes,
				agw3000c01v1Str2MulticEna
				IpaTxMode,
				agw3000c01v1VlanRx2Enable
				Bit0No1Yes,
				agw3000c01v1VlanRx2Id
				Uint12,
				agw3000c01v1LocalIpAdd3
				Uint8,
				agw3000c01v1LocalIpAdd2
				Uint8,
				agw3000c01v1LocalIpAdd1
				Uint8,
				agw3000c01v1LocalIpAdd0
				Uint8,
				agw3000c01v1LocalIpMask3
				Uint8,
				agw3000c01v1LocalIpMask2
				Uint8,
				agw3000c01v1LocalIpMask1
				Uint8,
				agw3000c01v1LocalIpMask0
				Uint8,
				agw3000c01v1LocalIpGway3
				Uint8,
				agw3000c01v1LocalIpGway2
				Uint8,
				agw3000c01v1LocalIpGway1
				Uint8,
				agw3000c01v1LocalIpGway0
				Uint8,
				agw3000c01v1Tx1UniEna
				Bit0No1Yes,
				agw3000c01v1Tx1MultiEna
				IpaTxMode,
				agw3000c01v1Tx1UipAdd3
				Uint8,
				agw3000c01v1Tx1UipAdd2
				Uint8,
				agw3000c01v1Tx1UipAdd1
				Uint8,
				agw3000c01v1Tx1UipAdd0
				Uint8,
				agw3000c01v1Tx1MipAdd3
				Uint8,
				agw3000c01v1Tx1MipAdd2
				Uint8,
				agw3000c01v1Tx1MipAdd1
				Uint8,
				agw3000c01v1Tx1MipAdd0
				Uint8,
				agw3000c01v1Tx1SPort
				Uint16,
				agw3000c01v1Tx1DPort
				Uint16,
				agw3000c01v1VlanTxEnable1
				Bit0No1Yes,
				agw3000c01v1VlanTxPrior1
				Uint3,
				agw3000c01v1VlanTxId1
				Uint12,
				agw3000c01v1Tx1LParam
				Uint5,
				agw3000c01v1Tx1FecMode
				FecMode,
				agw3000c01v1Tx1DParam
				Uint5,
				agw3000c01v1Tx1TspkInIppk
				Uint3,
				agw3000c01v1Tx1RowDelay
				Uint5,
				agw3000c01v1Tx1ColDelay
				Uint8,
				agw3000c01v1LowCost1
				Bit0No1Yes,
				agw3000c01v1HighReliab1
				Bit0No1Yes,
				agw3000c01v1HighThroughp1
				Bit0No1Yes,
				agw3000c01v1LowDelay1
				Bit0No1Yes,
				agw3000c01v1Precedence1
				IpaPrecedence,
				agw3000c01v1Ttl1
				Uint8,
				agw3000c01v1Str1IgmFAdd3
				Uint8,
				agw3000c01v1Str1IgmFAdd2
				Uint8,
				agw3000c01v1Str1IgmFAdd1
				Uint8,
				agw3000c01v1Str1IgmFAdd0
				Uint8,
				agw3000c01v1Str2IgmFAdd3
				Uint8,
				agw3000c01v1Str2IgmFAdd2
				Uint8,
				agw3000c01v1Str2IgmFAdd1
				Uint8,
				agw3000c01v1Str2IgmFAdd0
				Uint8,
				agw3000c01v1LocalIp2Add3
				Uint8,
				agw3000c01v1LocalIp2Add2
				Uint8,
				agw3000c01v1LocalIp2Add1
				Uint8,
				agw3000c01v1LocalIp2Add0
				Uint8,
				agw3000c01v1LocalIp2Msk3
				Uint8,
				agw3000c01v1LocalIp2Msk2
				Uint8,
				agw3000c01v1LocalIp2Msk1
				Uint8,
				agw3000c01v1LocalIp2Msk0
				Uint8,
				agw3000c01v1LocalIp2Gwy3
				Uint8,
				agw3000c01v1LocalIp2Gwy2
				Uint8,
				agw3000c01v1LocalIp2Gwy1
				Uint8,
				agw3000c01v1LocalIp2Gwy0
				Uint8,
				agw3000c01v1Tx2UniEna
				Bit0No1Yes,
				agw3000c01v1Tx2MultiEna
				IpaTxMode,
				agw3000c01v1Tx2UipAdd3
				Uint8,
				agw3000c01v1Tx2UipAdd2
				Uint8,
				agw3000c01v1Tx2UipAdd1
				Uint8,
				agw3000c01v1Tx2UipAdd0
				Uint8,
				agw3000c01v1Tx2MipAdd3
				Uint8,
				agw3000c01v1Tx2MipAdd2
				Uint8,
				agw3000c01v1Tx2MipAdd1
				Uint8,
				agw3000c01v1Tx2MipAdd0
				Uint8,
				agw3000c01v1Tx2SPort
				Uint16,
				agw3000c01v1Tx2DPort
				Uint16,
				agw3000c01v1VlanTxEnable2
				Bit0No1Yes,
				agw3000c01v1VlanTxPrior2
				Uint3,
				agw3000c01v1VlanTxId2
				Uint12,
				agw3000c01v1Tx2LParam
				Uint5,
				agw3000c01v1Tx2FecMode
				FecMode,
				agw3000c01v1Tx2DParam
				Uint5,
				agw3000c01v1Tx2TspkInIppk
				Uint3,
				agw3000c01v1Tx2RowDelay
				Uint5,
				agw3000c01v1Tx2ColDelay
				Uint8,
				agw3000c01v1LowCost2
				Bit0No1Yes,
				agw3000c01v1HighReliab2
				Bit0No1Yes,
				agw3000c01v1HighThroughp2
				Bit0No1Yes,
				agw3000c01v1LowDelay2
				Bit0No1Yes,
				agw3000c01v1Precedence2
				IpaPrecedence,
				agw3000c01v1Ttl2
				Uint8,
				agw3000c01v1Test0
				Uint8,
				agw3000c01v1Test1
				Uint8,
				agw3000c01v1Test2
				Uint8,
				agw3000c01v1Test3
				Uint8,
				agw3000c01v1Test4
				Uint8,
				agw3000c01v1Test5
				Uint8,
				agw3000c01v1AsiOut1Fail
				BitFail,
				agw3000c01v1AsiOut2Fail
				BitFail,
				agw3000c01v1IpOut1Fail
				BitFail,
				agw3000c01v1IpOut2Fail
				BitFail,
				agw3000c01v1AsiIn1Fail
				BitFail,
				agw3000c01v1AsiIn1FailTrapEnable
				AlarmEnable,
				agw3000c01v1ExAsiIn1Fail
				BitFail,
				agw3000c01v1ExAsiIn1FailTrapEnable
				AlarmEnable,
				agw3000c01v1AsiIn2Fail
				BitFail,
				agw3000c01v1AsiIn2FailTrapEnable
				AlarmEnable,
				agw3000c01v1ExAsiIn2Fail
				BitFail,
				agw3000c01v1ExAsiIn2FailTrapEnable
				AlarmEnable,
				agw3000c01v1IpIn1Fail
				BitFail,
				agw3000c01v1IpIn1FailTrapEnable
				AlarmEnable,
				agw3000c01v1ExIpIn1Fail
				BitFail,
				agw3000c01v1ExIpIn1FailTrapEnable
				AlarmEnable,
				agw3000c01v1IpIn2Fail
				BitFail,
				agw3000c01v1IpIn2FailTrapEnable
				AlarmEnable,
				agw3000c01v1ExIpIn2Fail
				BitFail,
				agw3000c01v1ExIpIn2FailTrapEnable
				AlarmEnable,
				agw3000c01v1DestAvailable1
				Bit0No1Yes,
				agw3000c01v1DestAvailable2
				Bit0No1Yes,
				agw3000c01v1BlindModStat1
				BlindModeStat,
				agw3000c01v1BlindModStat2
				BlindModeStat,
				agw3000c01v1AsiIn1Delay
				DelayX131Ms,
				agw3000c01v1AsiIn2Delay
				DelayX131Ms,
				agw3000c01v1IpIn1Delay
				DelayX131Ms,
				agw3000c01v1IpIn2Delay
				DelayX131Ms,
				agw3000c01v1IpRxAddress3
				Uint8,
				agw3000c01v1IpRxAddress2
				Uint8,
				agw3000c01v1IpRxAddress1
				Uint8,
				agw3000c01v1IpRxAddress0
				Uint8,
				agw3000c01v1IpRxPort
				Uint16,
				agw3000c01v1LParam
				Uint5,
				agw3000c01v1FecMode
				FecMode,
				agw3000c01v1PacketSize
				Bit02041188,
				agw3000c01v1DParam
				Uint5,
				agw3000c01v1TsPckInIpPck
				Uint3,
				agw3000c01v1PacketRate
				PacketRate,
				agw3000c01v1TimeSinceReset
				TimeS4,
				agw3000c01v1LostIpPck
				Uint16,
				agw3000c01v1RecoveredIpPck
				Uint16,
				agw3000c01v1OutOrdIpPck
				Uint16,
				agw3000c01v1FecRate
				PacketRate,
				agw3000c01v1Link
				IpaEtherStat,
				agw3000c01v1BufferStatus
				Rate1,
				agw3000c01v1PingStatus1
				IpaPingStat,
				agw3000c01v1PingStatus2
				IpaPingStat,
				agw3000c01v1SerialNo
				SerialNo,
				agw3000c01v1SpeedForce
				Bit0Ann1For,
				agw3000c01v1BadCrcPck
				Uint16,
				agw3000c01v1MaxDelayTxIp
				TimeX10Ms,
				agw3000c01v1InpFailMode
				Bit0Yes1No
			 }

		-- 1.3.6.1.4.1.10106.3.101291.1.1.1
		agw3000c01v1Index OBJECT-TYPE
			SYNTAX ModuleIndex
			MAX-ACCESS read-only
			STATUS current
			DESCRIPTION
				"Index of AGW3000C01V1 Table"
		::= { agw3000c01v1Entry 1 }

		-- 1.3.6.1.4.1.10106.3.101291.1.1.3
		agw3000c01v1Mode OBJECT-TYPE
			SYNTAX ChgOverMode2
			MAX-ACCESS read-write
			STATUS current
			DESCRIPTION
				"Allows selecting the switching mode"
		::= { agw3000c01v1Entry 3 }

		-- 1.3.6.1.4.1.10106.3.101291.1.1.4
		agw3000c01v1ModeTrapEnable OBJECT-TYPE
			SYNTAX AlarmEnable
			MAX-ACCESS read-write
			STATUS current
			DESCRIPTION
				"Allows selecting the switching mode Trap Enable"
		::= { agw3000c01v1Entry 4 }

		-- 1.3.6.1.4.1.10106.3.101291.1.1.5
		agw3000c01v1DvbTMode OBJECT-TYPE
			SYNTAX Bit0No1Yes
			MAX-ACCESS read-write
			STATUS current
			DESCRIPTION
				"Selects DVB-T mode. Seamless operation is only possible in DVB-T mode"
		::= { agw3000c01v1Entry 5 }

		-- 1.3.6.1.4.1.10106.3.101291.1.1.6
		agw3000c01v1DvbTModeTrapEnable OBJECT-TYPE
			SYNTAX AlarmEnable
			MAX-ACCESS read-write
			STATUS current
			DESCRIPTION
				"Selects DVB-T mode. Seamless operation is only possible in DVB-T mode Trap Enable"
		::= { agw3000c01v1Entry 6 }

		-- 1.3.6.1.4.1.10106.3.101291.1.1.7
		agw3000c01v1NullPckRtp OBJECT-TYPE
			SYNTAX Bit0No1Yes
			MAX-ACCESS read-write
			STATUS current
			DESCRIPTION
				"Selects if NULL packets are inserted if there are unrecovered packets when using RTP protocol"
		::= { agw3000c01v1Entry 7 }

		-- 1.3.6.1.4.1.10106.3.101291.1.1.9
		agw3000c01v1NarrowPllBw OBJECT-TYPE
			SYNTAX Bit0No1Yes
			MAX-ACCESS read-write
			STATUS current
			DESCRIPTION
				"Allows selecting a narrow PLL bandwidth in the clock packet PLL in non DVB-T mode to achieve a very stable bitrate"
		::= { agw3000c01v1Entry 9 }

		-- 1.3.6.1.4.1.10106.3.101291.1.1.11
		agw3000c01v1Buzzer OBJECT-TYPE
			SYNTAX BitMask
			MAX-ACCESS read-write
			STATUS current
			DESCRIPTION
				"Allows buzzer operation"
		::= { agw3000c01v1Entry 11 }

		-- 1.3.6.1.4.1.10106.3.101291.1.1.13
		agw3000c01v1GpioMode OBJECT-TYPE
			SYNTAX GpioMode
			MAX-ACCESS read-write
			STATUS current
			DESCRIPTION
				"Selects the GPIO's configurable mode"
		::= { agw3000c01v1Entry 13 }

		-- 1.3.6.1.4.1.10106.3.101291.1.1.15
		agw3000c01v1InputStChange OBJECT-TYPE
			SYNTAX Bit0No1Yes
			MAX-ACCESS read-write
			STATUS current
			DESCRIPTION
				"Signals a change in fail status"
		::= { agw3000c01v1Entry 15 }

		-- 1.3.6.1.4.1.10106.3.101291.1.1.17
		agw3000c01v1InputChange OBJECT-TYPE
			SYNTAX Bit0No1Yes
			MAX-ACCESS read-write
			STATUS current
			DESCRIPTION
				"Signals a change in selected input"
		::= { agw3000c01v1Entry 17 }

		-- 1.3.6.1.4.1.10106.3.101291.1.1.19
		agw3000c01v1EnaAsi1 OBJECT-TYPE
			SYNTAX BitMask
			MAX-ACCESS read-write
			STATUS current
			DESCRIPTION
				"Allows disabling ASI input 1 when it is not used"
		::= { agw3000c01v1Entry 19 }

		-- 1.3.6.1.4.1.10106.3.101291.1.1.21
		agw3000c01v1EnaAsi2 OBJECT-TYPE
			SYNTAX BitMask
			MAX-ACCESS read-write
			STATUS current
			DESCRIPTION
				"Allows disabling ASI input 2 when it is not used"
		::= { agw3000c01v1Entry 21 }

		-- 1.3.6.1.4.1.10106.3.101291.1.1.23
		agw3000c01v1EnaIp1 OBJECT-TYPE
			SYNTAX BitMask
			MAX-ACCESS read-write
			STATUS current
			DESCRIPTION
				"Allows disabling IP input 1 when it is not used"
		::= { agw3000c01v1Entry 23 }

		-- 1.3.6.1.4.1.10106.3.101291.1.1.25
		agw3000c01v1EnaIp2 OBJECT-TYPE
			SYNTAX BitMask
			MAX-ACCESS read-write
			STATUS current
			DESCRIPTION
				"Allows disabling IP input 2 when it is not used"
		::= { agw3000c01v1Entry 25 }

		-- 1.3.6.1.4.1.10106.3.101291.1.1.27
		agw3000c01v1AsiOut1In OBJECT-TYPE
			SYNTAX GatewayInput3
			MAX-ACCESS read-write
			STATUS current
			DESCRIPTION
				"ASI OUT 2 - Selected input"
		::= { agw3000c01v1Entry 27 }

		-- 1.3.6.1.4.1.10106.3.101291.1.1.28
		agw3000c01v1AsiOut1InTrapEnable OBJECT-TYPE
			SYNTAX AlarmEnable
			MAX-ACCESS read-write
			STATUS current
			DESCRIPTION
				"ASI OUT 2 - Selected input Trap Enable"
		::= { agw3000c01v1Entry 28 }

		-- 1.3.6.1.4.1.10106.3.101291.1.1.29
		agw3000c01v1AsiOut2In OBJECT-TYPE
			SYNTAX GatewayInput3
			MAX-ACCESS read-write
			STATUS current
			DESCRIPTION
				"ASI OUT 1 - Selected input"
		::= { agw3000c01v1Entry 29 }

		-- 1.3.6.1.4.1.10106.3.101291.1.1.30
		agw3000c01v1AsiOut2InTrapEnable OBJECT-TYPE
			SYNTAX AlarmEnable
			MAX-ACCESS read-write
			STATUS current
			DESCRIPTION
				"ASI OUT 1 - Selected input Trap Enable"
		::= { agw3000c01v1Entry 30 }

		-- 1.3.6.1.4.1.10106.3.101291.1.1.31
		agw3000c01v1IpOut1In OBJECT-TYPE
			SYNTAX GatewayInput3
			MAX-ACCESS read-write
			STATUS current
			DESCRIPTION
				"IP OUT 1 - Selected input"
		::= { agw3000c01v1Entry 31 }

		-- 1.3.6.1.4.1.10106.3.101291.1.1.32
		agw3000c01v1IpOut1InTrapEnable OBJECT-TYPE
			SYNTAX AlarmEnable
			MAX-ACCESS read-write
			STATUS current
			DESCRIPTION
				"IP OUT 1 - Selected input Trap Enable"
		::= { agw3000c01v1Entry 32 }

		-- 1.3.6.1.4.1.10106.3.101291.1.1.33
		agw3000c01v1IpOut2In OBJECT-TYPE
			SYNTAX GatewayInput3
			MAX-ACCESS read-write
			STATUS current
			DESCRIPTION
				"IP OUT 2 - Selected input"
		::= { agw3000c01v1Entry 33 }

		-- 1.3.6.1.4.1.10106.3.101291.1.1.34
		agw3000c01v1IpOut2InTrapEnable OBJECT-TYPE
			SYNTAX AlarmEnable
			MAX-ACCESS read-write
			STATUS current
			DESCRIPTION
				"IP OUT 2 - Selected input Trap Enable"
		::= { agw3000c01v1Entry 34 }

		-- 1.3.6.1.4.1.10106.3.101291.1.1.35
		agw3000c01v1PingEnable1 OBJECT-TYPE
			SYNTAX Bit0No1Yes
			MAX-ACCESS read-write
			STATUS current
			DESCRIPTION
				"Allows making a periodic ping to the unicast address"
		::= { agw3000c01v1Entry 35 }

		-- 1.3.6.1.4.1.10106.3.101291.1.1.37
		agw3000c01v1PingEnable2 OBJECT-TYPE
			SYNTAX Bit0No1Yes
			MAX-ACCESS read-write
			STATUS current
			DESCRIPTION
				"Allows making a periodic ping to the unicast address reserve"
		::= { agw3000c01v1Entry 37 }

		-- 1.3.6.1.4.1.10106.3.101291.1.1.39
		agw3000c01v1IpLinkFailEn OBJECT-TYPE
			SYNTAX Bit0No1Yes
			MAX-ACCESS read-write
			STATUS current
			DESCRIPTION
				"IP link lose signals fail in F_OUT GPO"
		::= { agw3000c01v1Entry 39 }

		-- 1.3.6.1.4.1.10106.3.101291.1.1.41
		agw3000c01v1IpDestFailEn OBJECT-TYPE
			SYNTAX Bit0No1Yes
			MAX-ACCESS read-write
			STATUS current
			DESCRIPTION
				"IP destination absence signals fail in F_OUT GPO"
		::= { agw3000c01v1Entry 41 }

		-- 1.3.6.1.4.1.10106.3.101291.1.1.43
		agw3000c01v1MaxTimeOut OBJECT-TYPE
			SYNTAX TimeX1Ms1
			MAX-ACCESS read-write
			STATUS current
			DESCRIPTION
				"Maximum time out for IP channels without receiving any packet.  It limits the low frequency jitter capacity."
		::= { agw3000c01v1Entry 43 }

		-- 1.3.6.1.4.1.10106.3.101291.1.1.45
		agw3000c01v1StatReset OBJECT-TYPE
			SYNTAX Bit0No1Yes
			MAX-ACCESS read-write
			STATUS current
			DESCRIPTION
				"Allows reseting the statistics measurements"
		::= { agw3000c01v1Entry 45 }

		-- 1.3.6.1.4.1.10106.3.101291.1.1.47
		agw3000c01v1StatSel OBJECT-TYPE
			SYNTAX Bit0Ipm1Ipr
			MAX-ACCESS read-write
			STATUS current
			DESCRIPTION
				"Allows selecting the channel to be displayed"
		::= { agw3000c01v1Entry 47 }

		-- 1.3.6.1.4.1.10106.3.101291.1.1.49
		agw3000c01v1StatMode OBJECT-TYPE
			SYNTAX Bit01s1Total
			MAX-ACCESS read-write
			STATUS current
			DESCRIPTION
				"Allows selecting the statistics mode"
		::= { agw3000c01v1Entry 49 }

		-- 1.3.6.1.4.1.10106.3.101291.1.1.51
		agw3000c01v1IgmpVersion OBJECT-TYPE
			SYNTAX Bit0V21V3
			MAX-ACCESS read-write
			STATUS current
			DESCRIPTION
				"Allows selecting the IGMP version"
		::= { agw3000c01v1Entry 51 }

		-- 1.3.6.1.4.1.10106.3.101291.1.1.53
		agw3000c01v1EthMode OBJECT-TYPE
			SYNTAX EthMode
			MAX-ACCESS read-write
			STATUS current
			DESCRIPTION
				"Allows selecting the Ethernet operating mode"
		::= { agw3000c01v1Entry 53 }

		-- 1.3.6.1.4.1.10106.3.101291.1.1.55
		agw3000c01v1PckDelAsiIn1 OBJECT-TYPE
			SYNTAX DelayPacket1
			MAX-ACCESS read-write
			STATUS current
			DESCRIPTION
				"Buffer size in packets for the ASI input 1"
		::= { agw3000c01v1Entry 55 }

		-- 1.3.6.1.4.1.10106.3.101291.1.1.57
		agw3000c01v1PckDelAsiIn2 OBJECT-TYPE
			SYNTAX DelayPacket1
			MAX-ACCESS read-write
			STATUS current
			DESCRIPTION
				"Buffer size in packets for the ASI input 2"
		::= { agw3000c01v1Entry 57 }

		-- 1.3.6.1.4.1.10106.3.101291.1.1.59
		agw3000c01v1PckDelIpIn1 OBJECT-TYPE
			SYNTAX DelayPacket1
			MAX-ACCESS read-write
			STATUS current
			DESCRIPTION
				"Buffer size in packets for the IP input 1"
		::= { agw3000c01v1Entry 59 }

		-- 1.3.6.1.4.1.10106.3.101291.1.1.61
		agw3000c01v1PckDelIpIn2 OBJECT-TYPE
			SYNTAX DelayPacket1
			MAX-ACCESS read-write
			STATUS current
			DESCRIPTION
				"Buffer size in packets for the IP input 2"
		::= { agw3000c01v1Entry 61 }

		-- 1.3.6.1.4.1.10106.3.101291.1.1.63
		agw3000c01v1AsiIn1Prior0 OBJECT-TYPE
			SYNTAX Uint2
			MAX-ACCESS read-write
			STATUS current
			DESCRIPTION
				"Allows selecting the ASI 1 input priority in output channel ASI OUT 1"
		::= { agw3000c01v1Entry 63 }

		-- 1.3.6.1.4.1.10106.3.101291.1.1.65
		agw3000c01v1AsiIn2Prior0 OBJECT-TYPE
			SYNTAX Uint2
			MAX-ACCESS read-write
			STATUS current
			DESCRIPTION
				"Allows selecting the ASI 2 input priority in output channel ASI OUT 1"
		::= { agw3000c01v1Entry 65 }

		-- 1.3.6.1.4.1.10106.3.101291.1.1.67
		agw3000c01v1IpIn1Prior0 OBJECT-TYPE
			SYNTAX Uint2
			MAX-ACCESS read-write
			STATUS current
			DESCRIPTION
				"Allows selecting the IP 1 input priority in output channel ASI OUT 1"
		::= { agw3000c01v1Entry 67 }

		-- 1.3.6.1.4.1.10106.3.101291.1.1.69
		agw3000c01v1IpIn2Prior0 OBJECT-TYPE
			SYNTAX Uint2
			MAX-ACCESS read-write
			STATUS current
			DESCRIPTION
				"Allows selecting the IP 2 input priority in output channel ASI OUT 1"
		::= { agw3000c01v1Entry 69 }

		-- 1.3.6.1.4.1.10106.3.101291.1.1.71
		agw3000c01v1AsiIn1Prior1 OBJECT-TYPE
			SYNTAX Uint2
			MAX-ACCESS read-write
			STATUS current
			DESCRIPTION
				"Allows selecting the ASI 1 input priority in output channel ASI OUT 2"
		::= { agw3000c01v1Entry 71 }

		-- 1.3.6.1.4.1.10106.3.101291.1.1.73
		agw3000c01v1AsiIn2Prior1 OBJECT-TYPE
			SYNTAX Uint2
			MAX-ACCESS read-write
			STATUS current
			DESCRIPTION
				"Allows selecting the ASI 2 input priority in output channel ASI OUT 2"
		::= { agw3000c01v1Entry 73 }

		-- 1.3.6.1.4.1.10106.3.101291.1.1.75
		agw3000c01v1IpIn1Prior1 OBJECT-TYPE
			SYNTAX Uint2
			MAX-ACCESS read-write
			STATUS current
			DESCRIPTION
				"Allows selecting the IP 1 input priority in output channel ASI OUT 2"
		::= { agw3000c01v1Entry 75 }

		-- 1.3.6.1.4.1.10106.3.101291.1.1.77
		agw3000c01v1IpIn2Prior1 OBJECT-TYPE
			SYNTAX Uint2
			MAX-ACCESS read-write
			STATUS current
			DESCRIPTION
				"Allows selecting the IP 2 input priority in output channel ASI OUT 2"
		::= { agw3000c01v1Entry 77 }

		-- 1.3.6.1.4.1.10106.3.101291.1.1.79
		agw3000c01v1AsiIn1Prior2 OBJECT-TYPE
			SYNTAX Uint2
			MAX-ACCESS read-write
			STATUS current
			DESCRIPTION
				"Allows selecting the ASI 1 input priority in output channel IP 1"
		::= { agw3000c01v1Entry 79 }

		-- 1.3.6.1.4.1.10106.3.101291.1.1.81
		agw3000c01v1AsiIn2Prior2 OBJECT-TYPE
			SYNTAX Uint2
			MAX-ACCESS read-write
			STATUS current
			DESCRIPTION
				"Allows selecting the ASI 2 input priority in output channel IP 1"
		::= { agw3000c01v1Entry 81 }

		-- 1.3.6.1.4.1.10106.3.101291.1.1.83
		agw3000c01v1IpIn1Prior2 OBJECT-TYPE
			SYNTAX Uint2
			MAX-ACCESS read-write
			STATUS current
			DESCRIPTION
				"Allows selecting the IP 1 input priority in output channel IP 1"
		::= { agw3000c01v1Entry 83 }

		-- 1.3.6.1.4.1.10106.3.101291.1.1.85
		agw3000c01v1IpIn2Prior2 OBJECT-TYPE
			SYNTAX Uint2
			MAX-ACCESS read-write
			STATUS current
			DESCRIPTION
				"Allows selecting the IP 2 input priority in output channel IP 1"
		::= { agw3000c01v1Entry 85 }

		-- 1.3.6.1.4.1.10106.3.101291.1.1.87
		agw3000c01v1AsiIn1Prior3 OBJECT-TYPE
			SYNTAX Uint2
			MAX-ACCESS read-write
			STATUS current
			DESCRIPTION
				"Allows selecting the ASI 1 input priority in output channel IP OUT 2"
		::= { agw3000c01v1Entry 87 }

		-- 1.3.6.1.4.1.10106.3.101291.1.1.89
		agw3000c01v1AsiIn2Prior3 OBJECT-TYPE
			SYNTAX Uint2
			MAX-ACCESS read-write
			STATUS current
			DESCRIPTION
				"Allows selecting the ASI 2 input priority in output channel IP OUT 2"
		::= { agw3000c01v1Entry 89 }

		-- 1.3.6.1.4.1.10106.3.101291.1.1.91
		agw3000c01v1IpIn1Prior3 OBJECT-TYPE
			SYNTAX Uint2
			MAX-ACCESS read-write
			STATUS current
			DESCRIPTION
				"Allows selecting the IP 1 input priority in output channel IP OUT 2"
		::= { agw3000c01v1Entry 91 }

		-- 1.3.6.1.4.1.10106.3.101291.1.1.93
		agw3000c01v1IpIn2Prior3 OBJECT-TYPE
			SYNTAX Uint2
			MAX-ACCESS read-write
			STATUS current
			DESCRIPTION
				"Allows selecting the IP 2 input priority in output channel IP OUT 2"
		::= { agw3000c01v1Entry 93 }

		-- 1.3.6.1.4.1.10106.3.101291.1.1.95
		agw3000c01v1ActivePreset OBJECT-TYPE
			SYNTAX Preset16Active
			MAX-ACCESS read-only
			STATUS current
			DESCRIPTION
				"Shows the active preset"
		::= { agw3000c01v1Entry 95 }

		-- 1.3.6.1.4.1.10106.3.101291.1.1.97
		agw3000c01v1LoadPreset OBJECT-TYPE
			SYNTAX Preset16Load
			MAX-ACCESS read-write
			STATUS current
			DESCRIPTION
				"Allows loading a preset"
		::= { agw3000c01v1Entry 97 }

		-- 1.3.6.1.4.1.10106.3.101291.1.1.99
		agw3000c01v1SavePreset OBJECT-TYPE
			SYNTAX Preset16Save
			MAX-ACCESS read-write
			STATUS current
			DESCRIPTION
				"Allows saving a preset"
		::= { agw3000c01v1Entry 99 }

		-- 1.3.6.1.4.1.10106.3.101291.1.1.101
		agw3000c01v1Str1UipDAdd3 OBJECT-TYPE
			SYNTAX Uint8
			MAX-ACCESS read-write
			STATUS current
			DESCRIPTION
				"Unicast IP address (3)"
		::= { agw3000c01v1Entry 101 }

		-- 1.3.6.1.4.1.10106.3.101291.1.1.103
		agw3000c01v1Str1UipDAdd2 OBJECT-TYPE
			SYNTAX Uint8
			MAX-ACCESS read-write
			STATUS current
			DESCRIPTION
				"Unicast IP address (2)"
		::= { agw3000c01v1Entry 103 }

		-- 1.3.6.1.4.1.10106.3.101291.1.1.105
		agw3000c01v1Str1UipDAdd1 OBJECT-TYPE
			SYNTAX Uint8
			MAX-ACCESS read-write
			STATUS current
			DESCRIPTION
				"Unicast IP address (1)"
		::= { agw3000c01v1Entry 105 }

		-- 1.3.6.1.4.1.10106.3.101291.1.1.107
		agw3000c01v1Str1UipDAdd0 OBJECT-TYPE
			SYNTAX Uint8
			MAX-ACCESS read-write
			STATUS current
			DESCRIPTION
				"Unicast IP address (0)"
		::= { agw3000c01v1Entry 107 }

		-- 1.3.6.1.4.1.10106.3.101291.1.1.109
		agw3000c01v1Str1MipDAdd3 OBJECT-TYPE
			SYNTAX Uint8
			MAX-ACCESS read-write
			STATUS current
			DESCRIPTION
				"Multicast IP address (3)"
		::= { agw3000c01v1Entry 109 }

		-- 1.3.6.1.4.1.10106.3.101291.1.1.111
		agw3000c01v1Str1MipDAdd2 OBJECT-TYPE
			SYNTAX Uint8
			MAX-ACCESS read-write
			STATUS current
			DESCRIPTION
				"Multicast IP address (2)"
		::= { agw3000c01v1Entry 111 }

		-- 1.3.6.1.4.1.10106.3.101291.1.1.113
		agw3000c01v1Str1MipDAdd1 OBJECT-TYPE
			SYNTAX Uint8
			MAX-ACCESS read-write
			STATUS current
			DESCRIPTION
				"Multicast IP address (1)"
		::= { agw3000c01v1Entry 113 }

		-- 1.3.6.1.4.1.10106.3.101291.1.1.115
		agw3000c01v1Str1MipDAdd0 OBJECT-TYPE
			SYNTAX Uint8
			MAX-ACCESS read-write
			STATUS current
			DESCRIPTION
				"Multicast IP address (0)"
		::= { agw3000c01v1Entry 115 }

		-- 1.3.6.1.4.1.10106.3.101291.1.1.117
		agw3000c01v1Str1DPort OBJECT-TYPE
			SYNTAX Uint16
			MAX-ACCESS read-write
			STATUS current
			DESCRIPTION
				"Destination port"
		::= { agw3000c01v1Entry 117 }

		-- 1.3.6.1.4.1.10106.3.101291.1.1.119
		agw3000c01v1Str1FecEna OBJECT-TYPE
			SYNTAX Bit0No1Yes
			MAX-ACCESS read-write
			STATUS current
			DESCRIPTION
				"Enable FEC"
		::= { agw3000c01v1Entry 119 }

		-- 1.3.6.1.4.1.10106.3.101291.1.1.121
		agw3000c01v1Str1MulticEna OBJECT-TYPE
			SYNTAX IpaTxMode
			MAX-ACCESS read-write
			STATUS current
			DESCRIPTION
				"RX mode"
		::= { agw3000c01v1Entry 121 }

		-- 1.3.6.1.4.1.10106.3.101291.1.1.123
		agw3000c01v1VlanRx1Enable OBJECT-TYPE
			SYNTAX Bit0No1Yes
			MAX-ACCESS read-write
			STATUS current
			DESCRIPTION
				"VLAN Enable"
		::= { agw3000c01v1Entry 123 }

		-- 1.3.6.1.4.1.10106.3.101291.1.1.125
		agw3000c01v1VlanRx1Id OBJECT-TYPE
			SYNTAX Uint12
			MAX-ACCESS read-write
			STATUS current
			DESCRIPTION
				"VLAN ID"
		::= { agw3000c01v1Entry 125 }

		-- 1.3.6.1.4.1.10106.3.101291.1.1.127
		agw3000c01v1Str2UipDAdd3 OBJECT-TYPE
			SYNTAX Uint8
			MAX-ACCESS read-write
			STATUS current
			DESCRIPTION
				"Unicast IP address (3)"
		::= { agw3000c01v1Entry 127 }

		-- 1.3.6.1.4.1.10106.3.101291.1.1.129
		agw3000c01v1Str2UipDAdd2 OBJECT-TYPE
			SYNTAX Uint8
			MAX-ACCESS read-write
			STATUS current
			DESCRIPTION
				"Unicast IP address (2)"
		::= { agw3000c01v1Entry 129 }

		-- 1.3.6.1.4.1.10106.3.101291.1.1.131
		agw3000c01v1Str2UipDAdd1 OBJECT-TYPE
			SYNTAX Uint8
			MAX-ACCESS read-write
			STATUS current
			DESCRIPTION
				"Unicast IP address (1)"
		::= { agw3000c01v1Entry 131 }

		-- 1.3.6.1.4.1.10106.3.101291.1.1.133
		agw3000c01v1Str2UipDAdd0 OBJECT-TYPE
			SYNTAX Uint8
			MAX-ACCESS read-write
			STATUS current
			DESCRIPTION
				"Unicast IP address (0)"
		::= { agw3000c01v1Entry 133 }

		-- 1.3.6.1.4.1.10106.3.101291.1.1.135
		agw3000c01v1Str2MipDAdd3 OBJECT-TYPE
			SYNTAX Uint8
			MAX-ACCESS read-write
			STATUS current
			DESCRIPTION
				"Multicast IP address (3)"
		::= { agw3000c01v1Entry 135 }

		-- 1.3.6.1.4.1.10106.3.101291.1.1.137
		agw3000c01v1Str2MipDAdd2 OBJECT-TYPE
			SYNTAX Uint8
			MAX-ACCESS read-write
			STATUS current
			DESCRIPTION
				"Multicast IP address (2)"
		::= { agw3000c01v1Entry 137 }

		-- 1.3.6.1.4.1.10106.3.101291.1.1.139
		agw3000c01v1Str2MipDAdd1 OBJECT-TYPE
			SYNTAX Uint8
			MAX-ACCESS read-write
			STATUS current
			DESCRIPTION
				"Multicast IP address (1)"
		::= { agw3000c01v1Entry 139 }

		-- 1.3.6.1.4.1.10106.3.101291.1.1.141
		agw3000c01v1Str2MipDAdd0 OBJECT-TYPE
			SYNTAX Uint8
			MAX-ACCESS read-write
			STATUS current
			DESCRIPTION
				"Multicast IP address (0)"
		::= { agw3000c01v1Entry 141 }

		-- 1.3.6.1.4.1.10106.3.101291.1.1.143
		agw3000c01v1Str2DPort OBJECT-TYPE
			SYNTAX Uint16
			MAX-ACCESS read-write
			STATUS current
			DESCRIPTION
				"Destination port"
		::= { agw3000c01v1Entry 143 }

		-- 1.3.6.1.4.1.10106.3.101291.1.1.145
		agw3000c01v1Str2FecEna OBJECT-TYPE
			SYNTAX Bit0No1Yes
			MAX-ACCESS read-write
			STATUS current
			DESCRIPTION
				"Enable FEC"
		::= { agw3000c01v1Entry 145 }

		-- 1.3.6.1.4.1.10106.3.101291.1.1.147
		agw3000c01v1Str2MulticEna OBJECT-TYPE
			SYNTAX IpaTxMode
			MAX-ACCESS read-write
			STATUS current
			DESCRIPTION
				"RX mode"
		::= { agw3000c01v1Entry 147 }

		-- 1.3.6.1.4.1.10106.3.101291.1.1.149
		agw3000c01v1VlanRx2Enable OBJECT-TYPE
			SYNTAX Bit0No1Yes
			MAX-ACCESS read-write
			STATUS current
			DESCRIPTION
				"VLAN Enable"
		::= { agw3000c01v1Entry 149 }

		-- 1.3.6.1.4.1.10106.3.101291.1.1.151
		agw3000c01v1VlanRx2Id OBJECT-TYPE
			SYNTAX Uint12
			MAX-ACCESS read-write
			STATUS current
			DESCRIPTION
				"VLAN ID"
		::= { agw3000c01v1Entry 151 }

		-- 1.3.6.1.4.1.10106.3.101291.1.1.153
		agw3000c01v1LocalIpAdd3 OBJECT-TYPE
			SYNTAX Uint8
			MAX-ACCESS read-write
			STATUS current
			DESCRIPTION
				"IP address (3)"
		::= { agw3000c01v1Entry 153 }

		-- 1.3.6.1.4.1.10106.3.101291.1.1.155
		agw3000c01v1LocalIpAdd2 OBJECT-TYPE
			SYNTAX Uint8
			MAX-ACCESS read-write
			STATUS current
			DESCRIPTION
				"IP address (2)"
		::= { agw3000c01v1Entry 155 }

		-- 1.3.6.1.4.1.10106.3.101291.1.1.157
		agw3000c01v1LocalIpAdd1 OBJECT-TYPE
			SYNTAX Uint8
			MAX-ACCESS read-write
			STATUS current
			DESCRIPTION
				"IP address (1)"
		::= { agw3000c01v1Entry 157 }

		-- 1.3.6.1.4.1.10106.3.101291.1.1.159
		agw3000c01v1LocalIpAdd0 OBJECT-TYPE
			SYNTAX Uint8
			MAX-ACCESS read-write
			STATUS current
			DESCRIPTION
				"IP address (0)"
		::= { agw3000c01v1Entry 159 }

		-- 1.3.6.1.4.1.10106.3.101291.1.1.161
		agw3000c01v1LocalIpMask3 OBJECT-TYPE
			SYNTAX Uint8
			MAX-ACCESS read-write
			STATUS current
			DESCRIPTION
				"IP mask (3)"
		::= { agw3000c01v1Entry 161 }

		-- 1.3.6.1.4.1.10106.3.101291.1.1.163
		agw3000c01v1LocalIpMask2 OBJECT-TYPE
			SYNTAX Uint8
			MAX-ACCESS read-write
			STATUS current
			DESCRIPTION
				"IP mask (2)"
		::= { agw3000c01v1Entry 163 }

		-- 1.3.6.1.4.1.10106.3.101291.1.1.165
		agw3000c01v1LocalIpMask1 OBJECT-TYPE
			SYNTAX Uint8
			MAX-ACCESS read-write
			STATUS current
			DESCRIPTION
				"IP mask (1)"
		::= { agw3000c01v1Entry 165 }

		-- 1.3.6.1.4.1.10106.3.101291.1.1.167
		agw3000c01v1LocalIpMask0 OBJECT-TYPE
			SYNTAX Uint8
			MAX-ACCESS read-write
			STATUS current
			DESCRIPTION
				"IP mask (0)"
		::= { agw3000c01v1Entry 167 }

		-- 1.3.6.1.4.1.10106.3.101291.1.1.169
		agw3000c01v1LocalIpGway3 OBJECT-TYPE
			SYNTAX Uint8
			MAX-ACCESS read-write
			STATUS current
			DESCRIPTION
				"Gateway IP address (3)"
		::= { agw3000c01v1Entry 169 }

		-- 1.3.6.1.4.1.10106.3.101291.1.1.171
		agw3000c01v1LocalIpGway2 OBJECT-TYPE
			SYNTAX Uint8
			MAX-ACCESS read-write
			STATUS current
			DESCRIPTION
				"Gateway IP address (2)"
		::= { agw3000c01v1Entry 171 }

		-- 1.3.6.1.4.1.10106.3.101291.1.1.173
		agw3000c01v1LocalIpGway1 OBJECT-TYPE
			SYNTAX Uint8
			MAX-ACCESS read-write
			STATUS current
			DESCRIPTION
				"Gateway IP address (1)"
		::= { agw3000c01v1Entry 173 }

		-- 1.3.6.1.4.1.10106.3.101291.1.1.175
		agw3000c01v1LocalIpGway0 OBJECT-TYPE
			SYNTAX Uint8
			MAX-ACCESS read-write
			STATUS current
			DESCRIPTION
				"Gateway IP address (0)"
		::= { agw3000c01v1Entry 175 }

		-- 1.3.6.1.4.1.10106.3.101291.1.1.177
		agw3000c01v1Tx1UniEna OBJECT-TYPE
			SYNTAX Bit0No1Yes
			MAX-ACCESS read-write
			STATUS current
			DESCRIPTION
				"Enable TX"
		::= { agw3000c01v1Entry 177 }

		-- 1.3.6.1.4.1.10106.3.101291.1.1.179
		agw3000c01v1Tx1MultiEna OBJECT-TYPE
			SYNTAX IpaTxMode
			MAX-ACCESS read-write
			STATUS current
			DESCRIPTION
				"TX mode"
		::= { agw3000c01v1Entry 179 }

		-- 1.3.6.1.4.1.10106.3.101291.1.1.181
		agw3000c01v1Tx1UipAdd3 OBJECT-TYPE
			SYNTAX Uint8
			MAX-ACCESS read-write
			STATUS current
			DESCRIPTION
				"Destination IP address (3)"
		::= { agw3000c01v1Entry 181 }

		-- 1.3.6.1.4.1.10106.3.101291.1.1.183
		agw3000c01v1Tx1UipAdd2 OBJECT-TYPE
			SYNTAX Uint8
			MAX-ACCESS read-write
			STATUS current
			DESCRIPTION
				"Destination IP address (2)"
		::= { agw3000c01v1Entry 183 }

		-- 1.3.6.1.4.1.10106.3.101291.1.1.185
		agw3000c01v1Tx1UipAdd1 OBJECT-TYPE
			SYNTAX Uint8
			MAX-ACCESS read-write
			STATUS current
			DESCRIPTION
				"Destination IP address (1)"
		::= { agw3000c01v1Entry 185 }

		-- 1.3.6.1.4.1.10106.3.101291.1.1.187
		agw3000c01v1Tx1UipAdd0 OBJECT-TYPE
			SYNTAX Uint8
			MAX-ACCESS read-write
			STATUS current
			DESCRIPTION
				"Destination IP address (0)"
		::= { agw3000c01v1Entry 187 }

		-- 1.3.6.1.4.1.10106.3.101291.1.1.189
		agw3000c01v1Tx1MipAdd3 OBJECT-TYPE
			SYNTAX Uint8
			MAX-ACCESS read-write
			STATUS current
			DESCRIPTION
				"Multicast dest. IP address (3)"
		::= { agw3000c01v1Entry 189 }

		-- 1.3.6.1.4.1.10106.3.101291.1.1.191
		agw3000c01v1Tx1MipAdd2 OBJECT-TYPE
			SYNTAX Uint8
			MAX-ACCESS read-write
			STATUS current
			DESCRIPTION
				"Multicast dest. IP address (2)"
		::= { agw3000c01v1Entry 191 }

		-- 1.3.6.1.4.1.10106.3.101291.1.1.193
		agw3000c01v1Tx1MipAdd1 OBJECT-TYPE
			SYNTAX Uint8
			MAX-ACCESS read-write
			STATUS current
			DESCRIPTION
				"Multicast dest. IP address (1)"
		::= { agw3000c01v1Entry 193 }

		-- 1.3.6.1.4.1.10106.3.101291.1.1.195
		agw3000c01v1Tx1MipAdd0 OBJECT-TYPE
			SYNTAX Uint8
			MAX-ACCESS read-write
			STATUS current
			DESCRIPTION
				"Multicast dest. IP address (0)"
		::= { agw3000c01v1Entry 195 }

		-- 1.3.6.1.4.1.10106.3.101291.1.1.197
		agw3000c01v1Tx1SPort OBJECT-TYPE
			SYNTAX Uint16
			MAX-ACCESS read-write
			STATUS current
			DESCRIPTION
				"Source port"
		::= { agw3000c01v1Entry 197 }

		-- 1.3.6.1.4.1.10106.3.101291.1.1.199
		agw3000c01v1Tx1DPort OBJECT-TYPE
			SYNTAX Uint16
			MAX-ACCESS read-write
			STATUS current
			DESCRIPTION
				"Destination port"
		::= { agw3000c01v1Entry 199 }

		-- 1.3.6.1.4.1.10106.3.101291.1.1.201
		agw3000c01v1VlanTxEnable1 OBJECT-TYPE
			SYNTAX Bit0No1Yes
			MAX-ACCESS read-write
			STATUS current
			DESCRIPTION
				"VLAN Enable"
		::= { agw3000c01v1Entry 201 }

		-- 1.3.6.1.4.1.10106.3.101291.1.1.203
		agw3000c01v1VlanTxPrior1 OBJECT-TYPE
			SYNTAX Uint3
			MAX-ACCESS read-write
			STATUS current
			DESCRIPTION
				"VLAN Priority"
		::= { agw3000c01v1Entry 203 }

		-- 1.3.6.1.4.1.10106.3.101291.1.1.205
		agw3000c01v1VlanTxId1 OBJECT-TYPE
			SYNTAX Uint12
			MAX-ACCESS read-write
			STATUS current
			DESCRIPTION
				"VLAN ID"
		::= { agw3000c01v1Entry 205 }

		-- 1.3.6.1.4.1.10106.3.101291.1.1.207
		agw3000c01v1Tx1LParam OBJECT-TYPE
			SYNTAX Uint5
			MAX-ACCESS read-write
			STATUS current
			DESCRIPTION
				"L parameter (FEC mode columns)"
		::= { agw3000c01v1Entry 207 }

		-- 1.3.6.1.4.1.10106.3.101291.1.1.209
		agw3000c01v1Tx1FecMode OBJECT-TYPE
			SYNTAX FecMode
			MAX-ACCESS read-write
			STATUS current
			DESCRIPTION
				"Protocol"
		::= { agw3000c01v1Entry 209 }

		-- 1.3.6.1.4.1.10106.3.101291.1.1.211
		agw3000c01v1Tx1DParam OBJECT-TYPE
			SYNTAX Uint5
			MAX-ACCESS read-write
			STATUS current
			DESCRIPTION
				"D parameter (FEC mode rows)"
		::= { agw3000c01v1Entry 211 }

		-- 1.3.6.1.4.1.10106.3.101291.1.1.213
		agw3000c01v1Tx1TspkInIppk OBJECT-TYPE
			SYNTAX Uint3
			MAX-ACCESS read-write
			STATUS current
			DESCRIPTION
				"TS packets in each IP packet"
		::= { agw3000c01v1Entry 213 }

		-- 1.3.6.1.4.1.10106.3.101291.1.1.215
		agw3000c01v1Tx1RowDelay OBJECT-TYPE
			SYNTAX Uint5
			MAX-ACCESS read-write
			STATUS current
			DESCRIPTION
				"FEC row delay"
		::= { agw3000c01v1Entry 215 }

		-- 1.3.6.1.4.1.10106.3.101291.1.1.217
		agw3000c01v1Tx1ColDelay OBJECT-TYPE
			SYNTAX Uint8
			MAX-ACCESS read-write
			STATUS current
			DESCRIPTION
				"FEC column delay"
		::= { agw3000c01v1Entry 217 }

		-- 1.3.6.1.4.1.10106.3.101291.1.1.219
		agw3000c01v1LowCost1 OBJECT-TYPE
			SYNTAX Bit0No1Yes
			MAX-ACCESS read-write
			STATUS current
			DESCRIPTION
				"TOS.  Low cost"
		::= { agw3000c01v1Entry 219 }

		-- 1.3.6.1.4.1.10106.3.101291.1.1.221
		agw3000c01v1HighReliab1 OBJECT-TYPE
			SYNTAX Bit0No1Yes
			MAX-ACCESS read-write
			STATUS current
			DESCRIPTION
				"TOS. High reliability"
		::= { agw3000c01v1Entry 221 }

		-- 1.3.6.1.4.1.10106.3.101291.1.1.223
		agw3000c01v1HighThroughp1 OBJECT-TYPE
			SYNTAX Bit0No1Yes
			MAX-ACCESS read-write
			STATUS current
			DESCRIPTION
				"TOS. High Throughput"
		::= { agw3000c01v1Entry 223 }

		-- 1.3.6.1.4.1.10106.3.101291.1.1.225
		agw3000c01v1LowDelay1 OBJECT-TYPE
			SYNTAX Bit0No1Yes
			MAX-ACCESS read-write
			STATUS current
			DESCRIPTION
				"TOS. Low delay"
		::= { agw3000c01v1Entry 225 }

		-- 1.3.6.1.4.1.10106.3.101291.1.1.227
		agw3000c01v1Precedence1 OBJECT-TYPE
			SYNTAX IpaPrecedence
			MAX-ACCESS read-write
			STATUS current
			DESCRIPTION
				"TOS. Precedence"
		::= { agw3000c01v1Entry 227 }

		-- 1.3.6.1.4.1.10106.3.101291.1.1.229
		agw3000c01v1Ttl1 OBJECT-TYPE
			SYNTAX Uint8
			MAX-ACCESS read-write
			STATUS current
			DESCRIPTION
				"Time to live"
		::= { agw3000c01v1Entry 229 }

		-- 1.3.6.1.4.1.10106.3.101291.1.1.231
		agw3000c01v1Str1IgmFAdd3 OBJECT-TYPE
			SYNTAX Uint8
			MAX-ACCESS read-write
			STATUS current
			DESCRIPTION
				"Source IP address (3)"
		::= { agw3000c01v1Entry 231 }

		-- 1.3.6.1.4.1.10106.3.101291.1.1.233
		agw3000c01v1Str1IgmFAdd2 OBJECT-TYPE
			SYNTAX Uint8
			MAX-ACCESS read-write
			STATUS current
			DESCRIPTION
				"Source IP address (2)"
		::= { agw3000c01v1Entry 233 }

		-- 1.3.6.1.4.1.10106.3.101291.1.1.235
		agw3000c01v1Str1IgmFAdd1 OBJECT-TYPE
			SYNTAX Uint8
			MAX-ACCESS read-write
			STATUS current
			DESCRIPTION
				"Source IP address (1)"
		::= { agw3000c01v1Entry 235 }

		-- 1.3.6.1.4.1.10106.3.101291.1.1.237
		agw3000c01v1Str1IgmFAdd0 OBJECT-TYPE
			SYNTAX Uint8
			MAX-ACCESS read-write
			STATUS current
			DESCRIPTION
				"Source IP address (0)"
		::= { agw3000c01v1Entry 237 }

		-- 1.3.6.1.4.1.10106.3.101291.1.1.239
		agw3000c01v1Str2IgmFAdd3 OBJECT-TYPE
			SYNTAX Uint8
			MAX-ACCESS read-write
			STATUS current
			DESCRIPTION
				"Source IP address (3)"
		::= { agw3000c01v1Entry 239 }

		-- 1.3.6.1.4.1.10106.3.101291.1.1.241
		agw3000c01v1Str2IgmFAdd2 OBJECT-TYPE
			SYNTAX Uint8
			MAX-ACCESS read-write
			STATUS current
			DESCRIPTION
				"Source IP address (2)"
		::= { agw3000c01v1Entry 241 }

		-- 1.3.6.1.4.1.10106.3.101291.1.1.243
		agw3000c01v1Str2IgmFAdd1 OBJECT-TYPE
			SYNTAX Uint8
			MAX-ACCESS read-write
			STATUS current
			DESCRIPTION
				"Source IP address (1)"
		::= { agw3000c01v1Entry 243 }

		-- 1.3.6.1.4.1.10106.3.101291.1.1.245
		agw3000c01v1Str2IgmFAdd0 OBJECT-TYPE
			SYNTAX Uint8
			MAX-ACCESS read-write
			STATUS current
			DESCRIPTION
				"Source IP address (0)"
		::= { agw3000c01v1Entry 245 }

		-- 1.3.6.1.4.1.10106.3.101291.1.1.247
		agw3000c01v1LocalIp2Add3 OBJECT-TYPE
			SYNTAX Uint8
			MAX-ACCESS read-write
			STATUS current
			DESCRIPTION
				"IP address (3)"
		::= { agw3000c01v1Entry 247 }

		-- 1.3.6.1.4.1.10106.3.101291.1.1.249
		agw3000c01v1LocalIp2Add2 OBJECT-TYPE
			SYNTAX Uint8
			MAX-ACCESS read-write
			STATUS current
			DESCRIPTION
				"IP address (2)"
		::= { agw3000c01v1Entry 249 }

		-- 1.3.6.1.4.1.10106.3.101291.1.1.251
		agw3000c01v1LocalIp2Add1 OBJECT-TYPE
			SYNTAX Uint8
			MAX-ACCESS read-write
			STATUS current
			DESCRIPTION
				"IP address (1)"
		::= { agw3000c01v1Entry 251 }

		-- 1.3.6.1.4.1.10106.3.101291.1.1.253
		agw3000c01v1LocalIp2Add0 OBJECT-TYPE
			SYNTAX Uint8
			MAX-ACCESS read-write
			STATUS current
			DESCRIPTION
				"IP address (0)"
		::= { agw3000c01v1Entry 253 }

		-- 1.3.6.1.4.1.10106.3.101291.1.1.255
		agw3000c01v1LocalIp2Msk3 OBJECT-TYPE
			SYNTAX Uint8
			MAX-ACCESS read-write
			STATUS current
			DESCRIPTION
				"IP mask (3)"
		::= { agw3000c01v1Entry 255 }

		-- 1.3.6.1.4.1.10106.3.101291.1.1.257
		agw3000c01v1LocalIp2Msk2 OBJECT-TYPE
			SYNTAX Uint8
			MAX-ACCESS read-write
			STATUS current
			DESCRIPTION
				"IP mask (2)"
		::= { agw3000c01v1Entry 257 }

		-- 1.3.6.1.4.1.10106.3.101291.1.1.259
		agw3000c01v1LocalIp2Msk1 OBJECT-TYPE
			SYNTAX Uint8
			MAX-ACCESS read-write
			STATUS current
			DESCRIPTION
				"IP mask (1)"
		::= { agw3000c01v1Entry 259 }

		-- 1.3.6.1.4.1.10106.3.101291.1.1.261
		agw3000c01v1LocalIp2Msk0 OBJECT-TYPE
			SYNTAX Uint8
			MAX-ACCESS read-write
			STATUS current
			DESCRIPTION
				"IP mask (0)"
		::= { agw3000c01v1Entry 261 }

		-- 1.3.6.1.4.1.10106.3.101291.1.1.263
		agw3000c01v1LocalIp2Gwy3 OBJECT-TYPE
			SYNTAX Uint8
			MAX-ACCESS read-write
			STATUS current
			DESCRIPTION
				"Gateway IP address (3)"
		::= { agw3000c01v1Entry 263 }

		-- 1.3.6.1.4.1.10106.3.101291.1.1.265
		agw3000c01v1LocalIp2Gwy2 OBJECT-TYPE
			SYNTAX Uint8
			MAX-ACCESS read-write
			STATUS current
			DESCRIPTION
				"Gateway IP address (2)"
		::= { agw3000c01v1Entry 265 }

		-- 1.3.6.1.4.1.10106.3.101291.1.1.267
		agw3000c01v1LocalIp2Gwy1 OBJECT-TYPE
			SYNTAX Uint8
			MAX-ACCESS read-write
			STATUS current
			DESCRIPTION
				"Gateway IP address (1)"
		::= { agw3000c01v1Entry 267 }

		-- 1.3.6.1.4.1.10106.3.101291.1.1.269
		agw3000c01v1LocalIp2Gwy0 OBJECT-TYPE
			SYNTAX Uint8
			MAX-ACCESS read-write
			STATUS current
			DESCRIPTION
				"Gateway IP address (0)"
		::= { agw3000c01v1Entry 269 }

		-- 1.3.6.1.4.1.10106.3.101291.1.1.271
		agw3000c01v1Tx2UniEna OBJECT-TYPE
			SYNTAX Bit0No1Yes
			MAX-ACCESS read-write
			STATUS current
			DESCRIPTION
				"Enable TX"
		::= { agw3000c01v1Entry 271 }

		-- 1.3.6.1.4.1.10106.3.101291.1.1.273
		agw3000c01v1Tx2MultiEna OBJECT-TYPE
			SYNTAX IpaTxMode
			MAX-ACCESS read-write
			STATUS current
			DESCRIPTION
				"TX mode"
		::= { agw3000c01v1Entry 273 }

		-- 1.3.6.1.4.1.10106.3.101291.1.1.275
		agw3000c01v1Tx2UipAdd3 OBJECT-TYPE
			SYNTAX Uint8
			MAX-ACCESS read-write
			STATUS current
			DESCRIPTION
				"Destination IP address (3)"
		::= { agw3000c01v1Entry 275 }

		-- 1.3.6.1.4.1.10106.3.101291.1.1.277
		agw3000c01v1Tx2UipAdd2 OBJECT-TYPE
			SYNTAX Uint8
			MAX-ACCESS read-write
			STATUS current
			DESCRIPTION
				"Destination IP address (2)"
		::= { agw3000c01v1Entry 277 }

		-- 1.3.6.1.4.1.10106.3.101291.1.1.279
		agw3000c01v1Tx2UipAdd1 OBJECT-TYPE
			SYNTAX Uint8
			MAX-ACCESS read-write
			STATUS current
			DESCRIPTION
				"Destination IP address (1)"
		::= { agw3000c01v1Entry 279 }

		-- 1.3.6.1.4.1.10106.3.101291.1.1.281
		agw3000c01v1Tx2UipAdd0 OBJECT-TYPE
			SYNTAX Uint8
			MAX-ACCESS read-write
			STATUS current
			DESCRIPTION
				"Destination IP address (0)"
		::= { agw3000c01v1Entry 281 }

		-- 1.3.6.1.4.1.10106.3.101291.1.1.283
		agw3000c01v1Tx2MipAdd3 OBJECT-TYPE
			SYNTAX Uint8
			MAX-ACCESS read-write
			STATUS current
			DESCRIPTION
				"Multicast dest. IP address (3)"
		::= { agw3000c01v1Entry 283 }

		-- 1.3.6.1.4.1.10106.3.101291.1.1.285
		agw3000c01v1Tx2MipAdd2 OBJECT-TYPE
			SYNTAX Uint8
			MAX-ACCESS read-write
			STATUS current
			DESCRIPTION
				"Multicast dest. IP address (2)"
		::= { agw3000c01v1Entry 285 }

		-- 1.3.6.1.4.1.10106.3.101291.1.1.287
		agw3000c01v1Tx2MipAdd1 OBJECT-TYPE
			SYNTAX Uint8
			MAX-ACCESS read-write
			STATUS current
			DESCRIPTION
				"Multicast dest. IP address (1)"
		::= { agw3000c01v1Entry 287 }

		-- 1.3.6.1.4.1.10106.3.101291.1.1.289
		agw3000c01v1Tx2MipAdd0 OBJECT-TYPE
			SYNTAX Uint8
			MAX-ACCESS read-write
			STATUS current
			DESCRIPTION
				"Multicast dest. IP address (0)"
		::= { agw3000c01v1Entry 289 }

		-- 1.3.6.1.4.1.10106.3.101291.1.1.291
		agw3000c01v1Tx2SPort OBJECT-TYPE
			SYNTAX Uint16
			MAX-ACCESS read-write
			STATUS current
			DESCRIPTION
				"Source port"
		::= { agw3000c01v1Entry 291 }

		-- 1.3.6.1.4.1.10106.3.101291.1.1.293
		agw3000c01v1Tx2DPort OBJECT-TYPE
			SYNTAX Uint16
			MAX-ACCESS read-write
			STATUS current
			DESCRIPTION
				"Destination port"
		::= { agw3000c01v1Entry 293 }

		-- 1.3.6.1.4.1.10106.3.101291.1.1.295
		agw3000c01v1VlanTxEnable2 OBJECT-TYPE
			SYNTAX Bit0No1Yes
			MAX-ACCESS read-write
			STATUS current
			DESCRIPTION
				"VLAN Enable"
		::= { agw3000c01v1Entry 295 }

		-- 1.3.6.1.4.1.10106.3.101291.1.1.297
		agw3000c01v1VlanTxPrior2 OBJECT-TYPE
			SYNTAX Uint3
			MAX-ACCESS read-write
			STATUS current
			DESCRIPTION
				"VLAN Priority"
		::= { agw3000c01v1Entry 297 }

		-- 1.3.6.1.4.1.10106.3.101291.1.1.299
		agw3000c01v1VlanTxId2 OBJECT-TYPE
			SYNTAX Uint12
			MAX-ACCESS read-write
			STATUS current
			DESCRIPTION
				"VLAN ID"
		::= { agw3000c01v1Entry 299 }

		-- 1.3.6.1.4.1.10106.3.101291.1.1.301
		agw3000c01v1Tx2LParam OBJECT-TYPE
			SYNTAX Uint5
			MAX-ACCESS read-write
			STATUS current
			DESCRIPTION
				"L parameter (FEC mode columns)"
		::= { agw3000c01v1Entry 301 }

		-- 1.3.6.1.4.1.10106.3.101291.1.1.303
		agw3000c01v1Tx2FecMode OBJECT-TYPE
			SYNTAX FecMode
			MAX-ACCESS read-write
			STATUS current
			DESCRIPTION
				"Protocol"
		::= { agw3000c01v1Entry 303 }

		-- 1.3.6.1.4.1.10106.3.101291.1.1.305
		agw3000c01v1Tx2DParam OBJECT-TYPE
			SYNTAX Uint5
			MAX-ACCESS read-write
			STATUS current
			DESCRIPTION
				"D parameter (FEC mode rows)"
		::= { agw3000c01v1Entry 305 }

		-- 1.3.6.1.4.1.10106.3.101291.1.1.307
		agw3000c01v1Tx2TspkInIppk OBJECT-TYPE
			SYNTAX Uint3
			MAX-ACCESS read-write
			STATUS current
			DESCRIPTION
				"TS packets in each IP packet"
		::= { agw3000c01v1Entry 307 }

		-- 1.3.6.1.4.1.10106.3.101291.1.1.309
		agw3000c01v1Tx2RowDelay OBJECT-TYPE
			SYNTAX Uint5
			MAX-ACCESS read-write
			STATUS current
			DESCRIPTION
				"FEC row delay"
		::= { agw3000c01v1Entry 309 }

		-- 1.3.6.1.4.1.10106.3.101291.1.1.311
		agw3000c01v1Tx2ColDelay OBJECT-TYPE
			SYNTAX Uint8
			MAX-ACCESS read-write
			STATUS current
			DESCRIPTION
				"FEC column delay"
		::= { agw3000c01v1Entry 311 }

		-- 1.3.6.1.4.1.10106.3.101291.1.1.313
		agw3000c01v1LowCost2 OBJECT-TYPE
			SYNTAX Bit0No1Yes
			MAX-ACCESS read-write
			STATUS current
			DESCRIPTION
				"TOS.  Low cost"
		::= { agw3000c01v1Entry 313 }

		-- 1.3.6.1.4.1.10106.3.101291.1.1.315
		agw3000c01v1HighReliab2 OBJECT-TYPE
			SYNTAX Bit0No1Yes
			MAX-ACCESS read-write
			STATUS current
			DESCRIPTION
				"TOS. High reliability"
		::= { agw3000c01v1Entry 315 }

		-- 1.3.6.1.4.1.10106.3.101291.1.1.317
		agw3000c01v1HighThroughp2 OBJECT-TYPE
			SYNTAX Bit0No1Yes
			MAX-ACCESS read-write
			STATUS current
			DESCRIPTION
				"TOS. High Throughput"
		::= { agw3000c01v1Entry 317 }

		-- 1.3.6.1.4.1.10106.3.101291.1.1.319
		agw3000c01v1LowDelay2 OBJECT-TYPE
			SYNTAX Bit0No1Yes
			MAX-ACCESS read-write
			STATUS current
			DESCRIPTION
				"TOS. Low delay"
		::= { agw3000c01v1Entry 319 }

		-- 1.3.6.1.4.1.10106.3.101291.1.1.321
		agw3000c01v1Precedence2 OBJECT-TYPE
			SYNTAX IpaPrecedence
			MAX-ACCESS read-write
			STATUS current
			DESCRIPTION
				"TOS. Precedence"
		::= { agw3000c01v1Entry 321 }

		-- 1.3.6.1.4.1.10106.3.101291.1.1.323
		agw3000c01v1Ttl2 OBJECT-TYPE
			SYNTAX Uint8
			MAX-ACCESS read-write
			STATUS current
			DESCRIPTION
				"Time to live"
		::= { agw3000c01v1Entry 323 }

		-- 1.3.6.1.4.1.10106.3.101291.1.1.325
		agw3000c01v1Test0 OBJECT-TYPE
			SYNTAX Uint8
			MAX-ACCESS read-write
			STATUS current
			DESCRIPTION
				"Test 0"
		::= { agw3000c01v1Entry 325 }

		-- 1.3.6.1.4.1.10106.3.101291.1.1.327
		agw3000c01v1Test1 OBJECT-TYPE
			SYNTAX Uint8
			MAX-ACCESS read-write
			STATUS current
			DESCRIPTION
				"Test 1"
		::= { agw3000c01v1Entry 327 }

		-- 1.3.6.1.4.1.10106.3.101291.1.1.329
		agw3000c01v1Test2 OBJECT-TYPE
			SYNTAX Uint8
			MAX-ACCESS read-write
			STATUS current
			DESCRIPTION
				"Test 2"
		::= { agw3000c01v1Entry 329 }

		-- 1.3.6.1.4.1.10106.3.101291.1.1.331
		agw3000c01v1Test3 OBJECT-TYPE
			SYNTAX Uint8
			MAX-ACCESS read-write
			STATUS current
			DESCRIPTION
				"Test 3"
		::= { agw3000c01v1Entry 331 }

		-- 1.3.6.1.4.1.10106.3.101291.1.1.333
		agw3000c01v1Test4 OBJECT-TYPE
			SYNTAX Uint8
			MAX-ACCESS read-write
			STATUS current
			DESCRIPTION
				"Test 4"
		::= { agw3000c01v1Entry 333 }

		-- 1.3.6.1.4.1.10106.3.101291.1.1.335
		agw3000c01v1Test5 OBJECT-TYPE
			SYNTAX Uint8
			MAX-ACCESS read-write
			STATUS current
			DESCRIPTION
				"Test 5"
		::= { agw3000c01v1Entry 335 }

		-- 1.3.6.1.4.1.10106.3.101291.1.1.337
		agw3000c01v1AsiOut1Fail OBJECT-TYPE
			SYNTAX BitFail
			MAX-ACCESS read-only
			STATUS current
			DESCRIPTION
				"The ASI 1 output signal is not valid because all inputs failed"
		::= { agw3000c01v1Entry 337 }

		-- 1.3.6.1.4.1.10106.3.101291.1.1.339
		agw3000c01v1AsiOut2Fail OBJECT-TYPE
			SYNTAX BitFail
			MAX-ACCESS read-only
			STATUS current
			DESCRIPTION
				"The ASI 2 output signal is not valid because all inputs failed"
		::= { agw3000c01v1Entry 339 }

		-- 1.3.6.1.4.1.10106.3.101291.1.1.341
		agw3000c01v1IpOut1Fail OBJECT-TYPE
			SYNTAX BitFail
			MAX-ACCESS read-only
			STATUS current
			DESCRIPTION
				"The IP 1 output signal is not valid because all inputs failed"
		::= { agw3000c01v1Entry 341 }

		-- 1.3.6.1.4.1.10106.3.101291.1.1.343
		agw3000c01v1IpOut2Fail OBJECT-TYPE
			SYNTAX BitFail
			MAX-ACCESS read-only
			STATUS current
			DESCRIPTION
				"The IP 2 output signal is not valid because all inputs failed"
		::= { agw3000c01v1Entry 343 }

		-- 1.3.6.1.4.1.10106.3.101291.1.1.345
		agw3000c01v1AsiIn1Fail OBJECT-TYPE
			SYNTAX BitFail
			MAX-ACCESS read-only
			STATUS current
			DESCRIPTION
				"ASI IN 1 fail status"
		::= { agw3000c01v1Entry 345 }

		-- 1.3.6.1.4.1.10106.3.101291.1.1.346
		agw3000c01v1AsiIn1FailTrapEnable OBJECT-TYPE
			SYNTAX AlarmEnable
			MAX-ACCESS read-write
			STATUS current
			DESCRIPTION
				"ASI IN 1 fail status Trap Enable"
		::= { agw3000c01v1Entry 346 }

		-- 1.3.6.1.4.1.10106.3.101291.1.1.347
		agw3000c01v1ExAsiIn1Fail OBJECT-TYPE
			SYNTAX BitFail
			MAX-ACCESS read-only
			STATUS current
			DESCRIPTION
				"ASI IN 1 external input fail status"
		::= { agw3000c01v1Entry 347 }

		-- 1.3.6.1.4.1.10106.3.101291.1.1.348
		agw3000c01v1ExAsiIn1FailTrapEnable OBJECT-TYPE
			SYNTAX AlarmEnable
			MAX-ACCESS read-write
			STATUS current
			DESCRIPTION
				"ASI IN 1 external input fail status Trap Enable"
		::= { agw3000c01v1Entry 348 }

		-- 1.3.6.1.4.1.10106.3.101291.1.1.349
		agw3000c01v1AsiIn2Fail OBJECT-TYPE
			SYNTAX BitFail
			MAX-ACCESS read-only
			STATUS current
			DESCRIPTION
				"ASI  IN 2 fail status"
		::= { agw3000c01v1Entry 349 }

		-- 1.3.6.1.4.1.10106.3.101291.1.1.350
		agw3000c01v1AsiIn2FailTrapEnable OBJECT-TYPE
			SYNTAX AlarmEnable
			MAX-ACCESS read-write
			STATUS current
			DESCRIPTION
				"ASI  IN 2 fail status Trap Enable"
		::= { agw3000c01v1Entry 350 }

		-- 1.3.6.1.4.1.10106.3.101291.1.1.351
		agw3000c01v1ExAsiIn2Fail OBJECT-TYPE
			SYNTAX BitFail
			MAX-ACCESS read-only
			STATUS current
			DESCRIPTION
				"ASI  IN 2 fail external input fail status"
		::= { agw3000c01v1Entry 351 }

		-- 1.3.6.1.4.1.10106.3.101291.1.1.352
		agw3000c01v1ExAsiIn2FailTrapEnable OBJECT-TYPE
			SYNTAX AlarmEnable
			MAX-ACCESS read-write
			STATUS current
			DESCRIPTION
				"ASI  IN 2 fail external input fail status Trap Enable"
		::= { agw3000c01v1Entry 352 }

		-- 1.3.6.1.4.1.10106.3.101291.1.1.353
		agw3000c01v1IpIn1Fail OBJECT-TYPE
			SYNTAX BitFail
			MAX-ACCESS read-only
			STATUS current
			DESCRIPTION
				"IP IN 1 fail status"
		::= { agw3000c01v1Entry 353 }

		-- 1.3.6.1.4.1.10106.3.101291.1.1.354
		agw3000c01v1IpIn1FailTrapEnable OBJECT-TYPE
			SYNTAX AlarmEnable
			MAX-ACCESS read-write
			STATUS current
			DESCRIPTION
				"IP IN 1 fail status Trap Enable"
		::= { agw3000c01v1Entry 354 }

		-- 1.3.6.1.4.1.10106.3.101291.1.1.355
		agw3000c01v1ExIpIn1Fail OBJECT-TYPE
			SYNTAX BitFail
			MAX-ACCESS read-only
			STATUS current
			DESCRIPTION
				"IP IN 1 external input fail status"
		::= { agw3000c01v1Entry 355 }

		-- 1.3.6.1.4.1.10106.3.101291.1.1.356
		agw3000c01v1ExIpIn1FailTrapEnable OBJECT-TYPE
			SYNTAX AlarmEnable
			MAX-ACCESS read-write
			STATUS current
			DESCRIPTION
				"IP IN 1 external input fail status Trap Enable"
		::= { agw3000c01v1Entry 356 }

		-- 1.3.6.1.4.1.10106.3.101291.1.1.357
		agw3000c01v1IpIn2Fail OBJECT-TYPE
			SYNTAX BitFail
			MAX-ACCESS read-only
			STATUS current
			DESCRIPTION
				"IP IN 2 input status"
		::= { agw3000c01v1Entry 357 }

		-- 1.3.6.1.4.1.10106.3.101291.1.1.358
		agw3000c01v1IpIn2FailTrapEnable OBJECT-TYPE
			SYNTAX AlarmEnable
			MAX-ACCESS read-write
			STATUS current
			DESCRIPTION
				"IP IN 2 input status Trap Enable"
		::= { agw3000c01v1Entry 358 }

		-- 1.3.6.1.4.1.10106.3.101291.1.1.359
		agw3000c01v1ExIpIn2Fail OBJECT-TYPE
			SYNTAX BitFail
			MAX-ACCESS read-only
			STATUS current
			DESCRIPTION
				"IP IN 2 external input fail status"
		::= { agw3000c01v1Entry 359 }

		-- 1.3.6.1.4.1.10106.3.101291.1.1.360
		agw3000c01v1ExIpIn2FailTrapEnable OBJECT-TYPE
			SYNTAX AlarmEnable
			MAX-ACCESS read-write
			STATUS current
			DESCRIPTION
				"IP IN 2 external input fail status Trap Enable"
		::= { agw3000c01v1Entry 360 }

		-- 1.3.6.1.4.1.10106.3.101291.1.1.361
		agw3000c01v1DestAvailable1 OBJECT-TYPE
			SYNTAX Bit0No1Yes
			MAX-ACCESS read-only
			STATUS current
			DESCRIPTION
				"Destination IP available"
		::= { agw3000c01v1Entry 361 }

		-- 1.3.6.1.4.1.10106.3.101291.1.1.363
		agw3000c01v1DestAvailable2 OBJECT-TYPE
			SYNTAX Bit0No1Yes
			MAX-ACCESS read-only
			STATUS current
			DESCRIPTION
				"Destination IP available"
		::= { agw3000c01v1Entry 363 }

		-- 1.3.6.1.4.1.10106.3.101291.1.1.365
		agw3000c01v1BlindModStat1 OBJECT-TYPE
			SYNTAX BlindModeStat
			MAX-ACCESS read-only
			STATUS current
			DESCRIPTION
				"Active receiver in blind mode"
		::= { agw3000c01v1Entry 365 }

		-- 1.3.6.1.4.1.10106.3.101291.1.1.367
		agw3000c01v1BlindModStat2 OBJECT-TYPE
			SYNTAX BlindModeStat
			MAX-ACCESS read-only
			STATUS current
			DESCRIPTION
				"Active receiver in blind mode"
		::= { agw3000c01v1Entry 367 }

		-- 1.3.6.1.4.1.10106.3.101291.1.1.369
		agw3000c01v1AsiIn1Delay OBJECT-TYPE
			SYNTAX DelayX131Ms
			MAX-ACCESS read-only
			STATUS current
			DESCRIPTION
				"ASI IN 1 to output delay"
		::= { agw3000c01v1Entry 369 }

		-- 1.3.6.1.4.1.10106.3.101291.1.1.371
		agw3000c01v1AsiIn2Delay OBJECT-TYPE
			SYNTAX DelayX131Ms
			MAX-ACCESS read-only
			STATUS current
			DESCRIPTION
				"ASI IN 2 to output delay"
		::= { agw3000c01v1Entry 371 }

		-- 1.3.6.1.4.1.10106.3.101291.1.1.373
		agw3000c01v1IpIn1Delay OBJECT-TYPE
			SYNTAX DelayX131Ms
			MAX-ACCESS read-only
			STATUS current
			DESCRIPTION
				"IP IN 1 to output delay"
		::= { agw3000c01v1Entry 373 }

		-- 1.3.6.1.4.1.10106.3.101291.1.1.375
		agw3000c01v1IpIn2Delay OBJECT-TYPE
			SYNTAX DelayX131Ms
			MAX-ACCESS read-only
			STATUS current
			DESCRIPTION
				"IP IN 2 to output delay"
		::= { agw3000c01v1Entry 375 }

		-- 1.3.6.1.4.1.10106.3.101291.1.1.377
		agw3000c01v1IpRxAddress3 OBJECT-TYPE
			SYNTAX Uint8
			MAX-ACCESS read-only
			STATUS current
			DESCRIPTION
				"RX packets source IP address (3)"
		::= { agw3000c01v1Entry 377 }

		-- 1.3.6.1.4.1.10106.3.101291.1.1.379
		agw3000c01v1IpRxAddress2 OBJECT-TYPE
			SYNTAX Uint8
			MAX-ACCESS read-only
			STATUS current
			DESCRIPTION
				"RX packets source IP address (2)"
		::= { agw3000c01v1Entry 379 }

		-- 1.3.6.1.4.1.10106.3.101291.1.1.381
		agw3000c01v1IpRxAddress1 OBJECT-TYPE
			SYNTAX Uint8
			MAX-ACCESS read-only
			STATUS current
			DESCRIPTION
				"RX packets source IP address (1)"
		::= { agw3000c01v1Entry 381 }

		-- 1.3.6.1.4.1.10106.3.101291.1.1.383
		agw3000c01v1IpRxAddress0 OBJECT-TYPE
			SYNTAX Uint8
			MAX-ACCESS read-only
			STATUS current
			DESCRIPTION
				"RX packets source IP address (0)"
		::= { agw3000c01v1Entry 383 }

		-- 1.3.6.1.4.1.10106.3.101291.1.1.385
		agw3000c01v1IpRxPort OBJECT-TYPE
			SYNTAX Uint16
			MAX-ACCESS read-only
			STATUS current
			DESCRIPTION
				"RX packets UDP source port"
		::= { agw3000c01v1Entry 385 }

		-- 1.3.6.1.4.1.10106.3.101291.1.1.387
		agw3000c01v1LParam OBJECT-TYPE
			SYNTAX Uint5
			MAX-ACCESS read-only
			STATUS current
			DESCRIPTION
				"L parameter (FEC mode columns)"
		::= { agw3000c01v1Entry 387 }

		-- 1.3.6.1.4.1.10106.3.101291.1.1.389
		agw3000c01v1FecMode OBJECT-TYPE
			SYNTAX FecMode
			MAX-ACCESS read-only
			STATUS current
			DESCRIPTION
				"Protocol"
		::= { agw3000c01v1Entry 389 }

		-- 1.3.6.1.4.1.10106.3.101291.1.1.391
		agw3000c01v1PacketSize OBJECT-TYPE
			SYNTAX Bit02041188
			MAX-ACCESS read-only
			STATUS current
			DESCRIPTION
				"Bytes in TS packets"
		::= { agw3000c01v1Entry 391 }

		-- 1.3.6.1.4.1.10106.3.101291.1.1.393
		agw3000c01v1DParam OBJECT-TYPE
			SYNTAX Uint5
			MAX-ACCESS read-only
			STATUS current
			DESCRIPTION
				"D parameter (FEC mode rows)"
		::= { agw3000c01v1Entry 393 }

		-- 1.3.6.1.4.1.10106.3.101291.1.1.395
		agw3000c01v1TsPckInIpPck OBJECT-TYPE
			SYNTAX Uint3
			MAX-ACCESS read-only
			STATUS current
			DESCRIPTION
				"TS packets in each IP packet"
		::= { agw3000c01v1Entry 395 }

		-- 1.3.6.1.4.1.10106.3.101291.1.1.397
		agw3000c01v1PacketRate OBJECT-TYPE
			SYNTAX PacketRate
			MAX-ACCESS read-only
			STATUS current
			DESCRIPTION
				"IP packet rate"
		::= { agw3000c01v1Entry 397 }

		-- 1.3.6.1.4.1.10106.3.101291.1.1.399
		agw3000c01v1TimeSinceReset OBJECT-TYPE
			SYNTAX TimeS4
			MAX-ACCESS read-only
			STATUS current
			DESCRIPTION
				"Elapsed time from last reset"
		::= { agw3000c01v1Entry 399 }

		-- 1.3.6.1.4.1.10106.3.101291.1.1.401
		agw3000c01v1LostIpPck OBJECT-TYPE
			SYNTAX Uint16
			MAX-ACCESS read-only
			STATUS current
			DESCRIPTION
				"Lost IP packets"
		::= { agw3000c01v1Entry 401 }

		-- 1.3.6.1.4.1.10106.3.101291.1.1.403
		agw3000c01v1RecoveredIpPck OBJECT-TYPE
			SYNTAX Uint16
			MAX-ACCESS read-only
			STATUS current
			DESCRIPTION
				"Recovered IP packets"
		::= { agw3000c01v1Entry 403 }

		-- 1.3.6.1.4.1.10106.3.101291.1.1.405
		agw3000c01v1OutOrdIpPck OBJECT-TYPE
			SYNTAX Uint16
			MAX-ACCESS read-only
			STATUS current
			DESCRIPTION
				"Out of order IP packets"
		::= { agw3000c01v1Entry 405 }

		-- 1.3.6.1.4.1.10106.3.101291.1.1.407
		agw3000c01v1FecRate OBJECT-TYPE
			SYNTAX PacketRate
			MAX-ACCESS read-only
			STATUS current
			DESCRIPTION
				"FEC packet rate"
		::= { agw3000c01v1Entry 407 }

		-- 1.3.6.1.4.1.10106.3.101291.1.1.409
		agw3000c01v1Link OBJECT-TYPE
			SYNTAX IpaEtherStat
			MAX-ACCESS read-only
			STATUS current
			DESCRIPTION
				"Ethernet conection status"
		::= { agw3000c01v1Entry 409 }

		-- 1.3.6.1.4.1.10106.3.101291.1.1.411
		agw3000c01v1BufferStatus OBJECT-TYPE
			SYNTAX Rate1
			MAX-ACCESS read-only
			STATUS current
			DESCRIPTION
				"Buffer filling status in non DVB-T mode"
		::= { agw3000c01v1Entry 411 }

		-- 1.3.6.1.4.1.10106.3.101291.1.1.413
		agw3000c01v1PingStatus1 OBJECT-TYPE
			SYNTAX IpaPingStat
			MAX-ACCESS read-only
			STATUS current
			DESCRIPTION
				"Ping status"
		::= { agw3000c01v1Entry 413 }

		-- 1.3.6.1.4.1.10106.3.101291.1.1.415
		agw3000c01v1PingStatus2 OBJECT-TYPE
			SYNTAX IpaPingStat
			MAX-ACCESS read-only
			STATUS current
			DESCRIPTION
				"Ping status"
		::= { agw3000c01v1Entry 415 }

		-- 1.3.6.1.4.1.10106.3.101291.1.1.417
		agw3000c01v1SerialNo OBJECT-TYPE
			SYNTAX SerialNo
			MAX-ACCESS read-only
			STATUS current
			DESCRIPTION
				"Serial number"
		::= { agw3000c01v1Entry 417 }

		-- 1.3.6.1.4.1.10106.3.101291.1.1.419
		agw3000c01v1SpeedForce OBJECT-TYPE
			SYNTAX Bit0Ann1For
			MAX-ACCESS read-write
			STATUS current
			DESCRIPTION
				"Allows selecting if the speed/mode is forced or announced for autonegotiation"
		::= { agw3000c01v1Entry 419 }

		-- 1.3.6.1.4.1.10106.3.101291.1.1.421
		agw3000c01v1BadCrcPck OBJECT-TYPE
			SYNTAX Uint16
			MAX-ACCESS read-only
			STATUS current
			DESCRIPTION
				"Bad CRC packets"
		::= { agw3000c01v1Entry 421 }

		-- 1.3.6.1.4.1.10106.3.101291.1.1.423
		agw3000c01v1MaxDelayTxIp OBJECT-TYPE
			SYNTAX TimeX10Ms
			MAX-ACCESS read-write
			STATUS current
			DESCRIPTION
				"Time before starting to transmit after recovering signal"
		::= { agw3000c01v1Entry 423 }

		-- 1.3.6.1.4.1.10106.3.101291.1.1.425
		agw3000c01v1InpFailMode OBJECT-TYPE
			SYNTAX Bit0Yes1No
			MAX-ACCESS read-write
			STATUS current
			DESCRIPTION
				"Selects if the output is muted when all the inputs fail"
		::= { agw3000c01v1Entry 425 }

		-- 1.3.6.1.4.1.10106.3.404702
		agw3000c01v2 OBJECT IDENTIFIER ::= { albalaProducts 404702 }

		-- 1.3.6.1.4.1.10106.3.404702.1
		agw3000c01v2Table  OBJECT-TYPE
			SYNTAX SEQUENCE OF Agw3000c01v2Entry
			MAX-ACCESS not-accessible
			STATUS current
			DESCRIPTION
				"Module  AGW3000C01V2 Table"
			::= { agw3000c01v2 1 }

		-- 1.3.6.1.4.1.10106.3.404702.1.1
		agw3000c01v2Entry  OBJECT-TYPE
			SYNTAX Agw3000c01v2Entry
			MAX-ACCESS not-accessible
			STATUS current
			DESCRIPTION
				"Module AGW3000C01V2 Entry"
			INDEX { agw3000c01v2Index }
			::= { agw3000c01v2Table 1 }

			Agw3000c01v2Entry ::=
			SEQUENCE {
				agw3000c01v2Index
				ModuleIndex,
				agw3000c01v2Mode
				ChgOverMode2,
				agw3000c01v2ModeTrapEnable
				AlarmEnable,
				agw3000c01v2DvbTMode
				Bit0No1Yes,
				agw3000c01v2DvbTModeTrapEnable
				AlarmEnable,
				agw3000c01v2NullPckRtp
				Bit0No1Yes,
				agw3000c01v2NarrowPllBw
				Bit0No1Yes,
				agw3000c01v2Buzzer
				BitMask,
				agw3000c01v2GpioMode
				GpioMode,
				agw3000c01v2InputStChange
				Bit0No1Yes,
				agw3000c01v2InputChange
				Bit0No1Yes,
				agw3000c01v2EnaAsi1
				BitMask,
				agw3000c01v2EnaAsi2
				BitMask,
				agw3000c01v2EnaIp1
				BitMask,
				agw3000c01v2EnaIp2
				BitMask,
				agw3000c01v2AsiOut1In
				GatewayInput3,
				agw3000c01v2AsiOut1InTrapEnable
				AlarmEnable,
				agw3000c01v2AsiOut2In
				GatewayInput3,
				agw3000c01v2AsiOut2InTrapEnable
				AlarmEnable,
				agw3000c01v2IpOut1In
				GatewayInput3,
				agw3000c01v2IpOut1InTrapEnable
				AlarmEnable,
				agw3000c01v2IpOut2In
				GatewayInput3,
				agw3000c01v2IpOut2InTrapEnable
				AlarmEnable,
				agw3000c01v2PingEnable1
				Bit0No1Yes,
				agw3000c01v2PingEnable2
				Bit0No1Yes,
				agw3000c01v2IpLinkFailEn
				Bit0No1Yes,
				agw3000c01v2IpDestFailEn
				Bit0No1Yes,
				agw3000c01v2MaxTimeOut
				TimeX1Ms1,
				agw3000c01v2StatReset
				Bit0No1Yes,
				agw3000c01v2StatSel
				Bit0Ipm1Ipr,
				agw3000c01v2StatMode
				Bit01s1Total,
				agw3000c01v2IgmpVersion
				Bit0V21V3,
				agw3000c01v2EthMode
				EthMode,
				agw3000c01v2SpeedForce
				Bit0Ann1For,
				agw3000c01v2PckDelAsiIn1
				DelayPacket1,
				agw3000c01v2PckDelAsiIn2
				DelayPacket1,
				agw3000c01v2PckDelIpIn1
				DelayPacket1,
				agw3000c01v2PckDelIpIn2
				DelayPacket1,
				agw3000c01v2AsiIn1Prior0
				Uint2,
				agw3000c01v2AsiIn2Prior0
				Uint2,
				agw3000c01v2IpIn1Prior0
				Uint2,
				agw3000c01v2IpIn2Prior0
				Uint2,
				agw3000c01v2AsiIn1Prior1
				Uint2,
				agw3000c01v2AsiIn2Prior1
				Uint2,
				agw3000c01v2IpIn1Prior1
				Uint2,
				agw3000c01v2IpIn2Prior1
				Uint2,
				agw3000c01v2AsiIn1Prior2
				Uint2,
				agw3000c01v2AsiIn2Prior2
				Uint2,
				agw3000c01v2IpIn1Prior2
				Uint2,
				agw3000c01v2IpIn2Prior2
				Uint2,
				agw3000c01v2AsiIn1Prior3
				Uint2,
				agw3000c01v2AsiIn2Prior3
				Uint2,
				agw3000c01v2IpIn1Prior3
				Uint2,
				agw3000c01v2IpIn2Prior3
				Uint2,
				agw3000c01v2ActivePreset
				Preset16Active,
				agw3000c01v2LoadPreset
				Preset16Load,
				agw3000c01v2SavePreset
				Preset16Save,
				agw3000c01v2Str1UipDAdd3
				Uint8,
				agw3000c01v2Str1UipDAdd2
				Uint8,
				agw3000c01v2Str1UipDAdd1
				Uint8,
				agw3000c01v2Str1UipDAdd0
				Uint8,
				agw3000c01v2Str1MipDAdd3
				Uint8,
				agw3000c01v2Str1MipDAdd2
				Uint8,
				agw3000c01v2Str1MipDAdd1
				Uint8,
				agw3000c01v2Str1MipDAdd0
				Uint8,
				agw3000c01v2Str1DPort
				Uint16,
				agw3000c01v2Str1FecEna
				Bit0No1Yes,
				agw3000c01v2Str1MulticEna
				IpaTxMode,
				agw3000c01v2VlanRx1Enable
				Bit0No1Yes,
				agw3000c01v2VlanRx1Id
				Uint12,
				agw3000c01v2Str2UipDAdd3
				Uint8,
				agw3000c01v2Str2UipDAdd2
				Uint8,
				agw3000c01v2Str2UipDAdd1
				Uint8,
				agw3000c01v2Str2UipDAdd0
				Uint8,
				agw3000c01v2Str2MipDAdd3
				Uint8,
				agw3000c01v2Str2MipDAdd2
				Uint8,
				agw3000c01v2Str2MipDAdd1
				Uint8,
				agw3000c01v2Str2MipDAdd0
				Uint8,
				agw3000c01v2Str2DPort
				Uint16,
				agw3000c01v2Str2FecEna
				Bit0No1Yes,
				agw3000c01v2Str2MulticEna
				IpaTxMode,
				agw3000c01v2VlanRx2Enable
				Bit0No1Yes,
				agw3000c01v2VlanRx2Id
				Uint12,
				agw3000c01v2LocalIpAdd3
				Uint8,
				agw3000c01v2LocalIpAdd2
				Uint8,
				agw3000c01v2LocalIpAdd1
				Uint8,
				agw3000c01v2LocalIpAdd0
				Uint8,
				agw3000c01v2LocalIpMask3
				Uint8,
				agw3000c01v2LocalIpMask2
				Uint8,
				agw3000c01v2LocalIpMask1
				Uint8,
				agw3000c01v2LocalIpMask0
				Uint8,
				agw3000c01v2LocalIpGway3
				Uint8,
				agw3000c01v2LocalIpGway2
				Uint8,
				agw3000c01v2LocalIpGway1
				Uint8,
				agw3000c01v2LocalIpGway0
				Uint8,
				agw3000c01v2Tx1UniEna
				Bit0No1Yes,
				agw3000c01v2Tx1MultiEna
				IpaTxMode,
				agw3000c01v2Tx1UipAdd3
				Uint8,
				agw3000c01v2Tx1UipAdd2
				Uint8,
				agw3000c01v2Tx1UipAdd1
				Uint8,
				agw3000c01v2Tx1UipAdd0
				Uint8,
				agw3000c01v2Tx1MipAdd3
				Uint8,
				agw3000c01v2Tx1MipAdd2
				Uint8,
				agw3000c01v2Tx1MipAdd1
				Uint8,
				agw3000c01v2Tx1MipAdd0
				Uint8,
				agw3000c01v2Tx1SPort
				Uint16,
				agw3000c01v2Tx1DPort
				Uint16,
				agw3000c01v2VlanTxEnable1
				Bit0No1Yes,
				agw3000c01v2VlanTxPrior1
				Uint3,
				agw3000c01v2VlanTxId1
				Uint12,
				agw3000c01v2Tx1LParam
				Uint5,
				agw3000c01v2Tx1FecMode
				FecMode,
				agw3000c01v2Tx1DParam
				Uint5,
				agw3000c01v2Tx1TspkInIppk
				Uint3,
				agw3000c01v2Tx1RowDelay
				Uint5,
				agw3000c01v2Tx1ColDelay
				Uint8,
				agw3000c01v2LowCost1
				Bit0No1Yes,
				agw3000c01v2HighReliab1
				Bit0No1Yes,
				agw3000c01v2HighThroughp1
				Bit0No1Yes,
				agw3000c01v2LowDelay1
				Bit0No1Yes,
				agw3000c01v2Precedence1
				IpaPrecedence,
				agw3000c01v2Ttl1
				Uint8,
				agw3000c01v2Str1IgmFAdd3
				Uint8,
				agw3000c01v2Str1IgmFAdd2
				Uint8,
				agw3000c01v2Str1IgmFAdd1
				Uint8,
				agw3000c01v2Str1IgmFAdd0
				Uint8,
				agw3000c01v2Str2IgmFAdd3
				Uint8,
				agw3000c01v2Str2IgmFAdd2
				Uint8,
				agw3000c01v2Str2IgmFAdd1
				Uint8,
				agw3000c01v2Str2IgmFAdd0
				Uint8,
				agw3000c01v2LocalIp2Add3
				Uint8,
				agw3000c01v2LocalIp2Add2
				Uint8,
				agw3000c01v2LocalIp2Add1
				Uint8,
				agw3000c01v2LocalIp2Add0
				Uint8,
				agw3000c01v2LocalIp2Msk3
				Uint8,
				agw3000c01v2LocalIp2Msk2
				Uint8,
				agw3000c01v2LocalIp2Msk1
				Uint8,
				agw3000c01v2LocalIp2Msk0
				Uint8,
				agw3000c01v2LocalIp2Gwy3
				Uint8,
				agw3000c01v2LocalIp2Gwy2
				Uint8,
				agw3000c01v2LocalIp2Gwy1
				Uint8,
				agw3000c01v2LocalIp2Gwy0
				Uint8,
				agw3000c01v2Tx2UniEna
				Bit0No1Yes,
				agw3000c01v2Tx2MultiEna
				IpaTxMode,
				agw3000c01v2Tx2UipAdd3
				Uint8,
				agw3000c01v2Tx2UipAdd2
				Uint8,
				agw3000c01v2Tx2UipAdd1
				Uint8,
				agw3000c01v2Tx2UipAdd0
				Uint8,
				agw3000c01v2Tx2MipAdd3
				Uint8,
				agw3000c01v2Tx2MipAdd2
				Uint8,
				agw3000c01v2Tx2MipAdd1
				Uint8,
				agw3000c01v2Tx2MipAdd0
				Uint8,
				agw3000c01v2Tx2SPort
				Uint16,
				agw3000c01v2Tx2DPort
				Uint16,
				agw3000c01v2VlanTxEnable2
				Bit0No1Yes,
				agw3000c01v2VlanTxPrior2
				Uint3,
				agw3000c01v2VlanTxId2
				Uint12,
				agw3000c01v2Tx2LParam
				Uint5,
				agw3000c01v2Tx2FecMode
				FecMode,
				agw3000c01v2Tx2DParam
				Uint5,
				agw3000c01v2Tx2TspkInIppk
				Uint3,
				agw3000c01v2Tx2RowDelay
				Uint5,
				agw3000c01v2Tx2ColDelay
				Uint8,
				agw3000c01v2LowCost2
				Bit0No1Yes,
				agw3000c01v2HighReliab2
				Bit0No1Yes,
				agw3000c01v2HighThroughp2
				Bit0No1Yes,
				agw3000c01v2LowDelay2
				Bit0No1Yes,
				agw3000c01v2Precedence2
				IpaPrecedence,
				agw3000c01v2Ttl2
				Uint8,
				agw3000c01v2Test0
				Uint8,
				agw3000c01v2Test1
				Uint8,
				agw3000c01v2Test2
				Uint8,
				agw3000c01v2Test3
				Uint8,
				agw3000c01v2Test4
				Uint8,
				agw3000c01v2Test5
				Uint8,
				agw3000c01v2AsiOut1Fail
				BitFail,
				agw3000c01v2AsiOut2Fail
				BitFail,
				agw3000c01v2IpOut1Fail
				BitFail,
				agw3000c01v2IpOut2Fail
				BitFail,
				agw3000c01v2AsiIn1Fail
				BitFail,
				agw3000c01v2AsiIn1FailTrapEnable
				AlarmEnable,
				agw3000c01v2ExAsiIn1Fail
				BitFail,
				agw3000c01v2ExAsiIn1FailTrapEnable
				AlarmEnable,
				agw3000c01v2AsiIn2Fail
				BitFail,
				agw3000c01v2AsiIn2FailTrapEnable
				AlarmEnable,
				agw3000c01v2ExAsiIn2Fail
				BitFail,
				agw3000c01v2ExAsiIn2FailTrapEnable
				AlarmEnable,
				agw3000c01v2IpIn1Fail
				BitFail,
				agw3000c01v2IpIn1FailTrapEnable
				AlarmEnable,
				agw3000c01v2ExIpIn1Fail
				BitFail,
				agw3000c01v2ExIpIn1FailTrapEnable
				AlarmEnable,
				agw3000c01v2IpIn2Fail
				BitFail,
				agw3000c01v2IpIn2FailTrapEnable
				AlarmEnable,
				agw3000c01v2ExIpIn2Fail
				BitFail,
				agw3000c01v2ExIpIn2FailTrapEnable
				AlarmEnable,
				agw3000c01v2DestAvailable1
				Bit0No1Yes,
				agw3000c01v2DestAvailable2
				Bit0No1Yes,
				agw3000c01v2BlindModStat1
				BlindModeStat,
				agw3000c01v2BlindModStat2
				BlindModeStat,
				agw3000c01v2AsiIn1Delay
				DelayX131Ms,
				agw3000c01v2AsiIn2Delay
				DelayX131Ms,
				agw3000c01v2IpIn1Delay
				DelayX131Ms,
				agw3000c01v2IpIn2Delay
				DelayX131Ms,
				agw3000c01v2IpRxAddress3
				Uint8,
				agw3000c01v2IpRxAddress2
				Uint8,
				agw3000c01v2IpRxAddress1
				Uint8,
				agw3000c01v2IpRxAddress0
				Uint8,
				agw3000c01v2IpRxPort
				Uint16,
				agw3000c01v2LParam
				Uint5,
				agw3000c01v2FecMode
				FecMode,
				agw3000c01v2PacketSize
				Bit02041188,
				agw3000c01v2DParam
				Uint5,
				agw3000c01v2TsPckInIpPck
				Uint3,
				agw3000c01v2PacketRate
				PacketRate,
				agw3000c01v2TimeSinceReset
				TimeS4,
				agw3000c01v2LostIpPck
				Uint16,
				agw3000c01v2RecoveredIpPck
				Uint16,
				agw3000c01v2BadCrcPck
				Uint16,
				agw3000c01v2OutOrdIpPck
				Uint16,
				agw3000c01v2FecRate
				PacketRate,
				agw3000c01v2Link
				IpaEtherStat,
				agw3000c01v2BufferStatus
				Rate1,
				agw3000c01v2PingStatus1
				IpaPingStat,
				agw3000c01v2PingStatus2
				IpaPingStat,
				agw3000c01v2SerialNo
				SerialNo,
				agw3000c01v2MaxDelayTxIp
				TimeX10Ms,
				agw3000c01v2InpFailMode
				Bit0Yes1No
			 }

		-- 1.3.6.1.4.1.10106.3.101291.1.1.1
		agw3000c01v2Index OBJECT-TYPE
			SYNTAX ModuleIndex
			MAX-ACCESS read-only
			STATUS current
			DESCRIPTION
				"Index of AGW3000C01V2 Table"
		::= { agw3000c01v2Entry 1 }

		-- 1.3.6.1.4.1.10106.3.101291.1.1.3
		agw3000c01v2Mode OBJECT-TYPE
			SYNTAX ChgOverMode2
			MAX-ACCESS read-write
			STATUS current
			DESCRIPTION
				"Allows selecting the switching mode"
		::= { agw3000c01v2Entry 3 }

		-- 1.3.6.1.4.1.10106.3.101291.1.1.4
		agw3000c01v2ModeTrapEnable OBJECT-TYPE
			SYNTAX AlarmEnable
			MAX-ACCESS read-write
			STATUS current
			DESCRIPTION
				"Allows selecting the switching mode Trap Enable"
		::= { agw3000c01v2Entry 4 }

		-- 1.3.6.1.4.1.10106.3.101291.1.1.5
		agw3000c01v2DvbTMode OBJECT-TYPE
			SYNTAX Bit0No1Yes
			MAX-ACCESS read-write
			STATUS current
			DESCRIPTION
				"Selects DVB-T mode. Seamless operation is only possible in DVB-T mode"
		::= { agw3000c01v2Entry 5 }

		-- 1.3.6.1.4.1.10106.3.101291.1.1.6
		agw3000c01v2DvbTModeTrapEnable OBJECT-TYPE
			SYNTAX AlarmEnable
			MAX-ACCESS read-write
			STATUS current
			DESCRIPTION
				"Selects DVB-T mode. Seamless operation is only possible in DVB-T mode Trap Enable"
		::= { agw3000c01v2Entry 6 }

		-- 1.3.6.1.4.1.10106.3.101291.1.1.7
		agw3000c01v2NullPckRtp OBJECT-TYPE
			SYNTAX Bit0No1Yes
			MAX-ACCESS read-write
			STATUS current
			DESCRIPTION
				"Selects if NULL packets are inserted if there are unrecovered packets when using RTP protocol"
		::= { agw3000c01v2Entry 7 }

		-- 1.3.6.1.4.1.10106.3.101291.1.1.9
		agw3000c01v2NarrowPllBw OBJECT-TYPE
			SYNTAX Bit0No1Yes
			MAX-ACCESS read-write
			STATUS current
			DESCRIPTION
				"Allows selecting a narrow PLL bandwidth in the clock packet PLL in non DVB-T mode to achieve a very stable bitrate"
		::= { agw3000c01v2Entry 9 }

		-- 1.3.6.1.4.1.10106.3.101291.1.1.11
		agw3000c01v2Buzzer OBJECT-TYPE
			SYNTAX BitMask
			MAX-ACCESS read-write
			STATUS current
			DESCRIPTION
				"Allows buzzer operation"
		::= { agw3000c01v2Entry 11 }

		-- 1.3.6.1.4.1.10106.3.101291.1.1.13
		agw3000c01v2GpioMode OBJECT-TYPE
			SYNTAX GpioMode
			MAX-ACCESS read-write
			STATUS current
			DESCRIPTION
				"Selects the GPIO's configurable mode"
		::= { agw3000c01v2Entry 13 }

		-- 1.3.6.1.4.1.10106.3.101291.1.1.15
		agw3000c01v2InputStChange OBJECT-TYPE
			SYNTAX Bit0No1Yes
			MAX-ACCESS read-write
			STATUS current
			DESCRIPTION
				"Signals a change in fail status"
		::= { agw3000c01v2Entry 15 }

		-- 1.3.6.1.4.1.10106.3.101291.1.1.17
		agw3000c01v2InputChange OBJECT-TYPE
			SYNTAX Bit0No1Yes
			MAX-ACCESS read-write
			STATUS current
			DESCRIPTION
				"Signals a change in selected input"
		::= { agw3000c01v2Entry 17 }

		-- 1.3.6.1.4.1.10106.3.101291.1.1.19
		agw3000c01v2EnaAsi1 OBJECT-TYPE
			SYNTAX BitMask
			MAX-ACCESS read-write
			STATUS current
			DESCRIPTION
				"Allows disabling ASI input 1 when it is not used"
		::= { agw3000c01v2Entry 19 }

		-- 1.3.6.1.4.1.10106.3.101291.1.1.21
		agw3000c01v2EnaAsi2 OBJECT-TYPE
			SYNTAX BitMask
			MAX-ACCESS read-write
			STATUS current
			DESCRIPTION
				"Allows disabling ASI input 2 when it is not used"
		::= { agw3000c01v2Entry 21 }

		-- 1.3.6.1.4.1.10106.3.101291.1.1.23
		agw3000c01v2EnaIp1 OBJECT-TYPE
			SYNTAX BitMask
			MAX-ACCESS read-write
			STATUS current
			DESCRIPTION
				"Allows disabling IP input 1 when it is not used"
		::= { agw3000c01v2Entry 23 }

		-- 1.3.6.1.4.1.10106.3.101291.1.1.25
		agw3000c01v2EnaIp2 OBJECT-TYPE
			SYNTAX BitMask
			MAX-ACCESS read-write
			STATUS current
			DESCRIPTION
				"Allows disabling IP input 2 when it is not used"
		::= { agw3000c01v2Entry 25 }

		-- 1.3.6.1.4.1.10106.3.101291.1.1.27
		agw3000c01v2AsiOut1In OBJECT-TYPE
			SYNTAX GatewayInput3
			MAX-ACCESS read-write
			STATUS current
			DESCRIPTION
				"ASI OUT 2 - Selected input"
		::= { agw3000c01v2Entry 27 }

		-- 1.3.6.1.4.1.10106.3.101291.1.1.28
		agw3000c01v2AsiOut1InTrapEnable OBJECT-TYPE
			SYNTAX AlarmEnable
			MAX-ACCESS read-write
			STATUS current
			DESCRIPTION
				"ASI OUT 2 - Selected input Trap Enable"
		::= { agw3000c01v2Entry 28 }

		-- 1.3.6.1.4.1.10106.3.101291.1.1.29
		agw3000c01v2AsiOut2In OBJECT-TYPE
			SYNTAX GatewayInput3
			MAX-ACCESS read-write
			STATUS current
			DESCRIPTION
				"ASI OUT 1 - Selected input"
		::= { agw3000c01v2Entry 29 }

		-- 1.3.6.1.4.1.10106.3.101291.1.1.30
		agw3000c01v2AsiOut2InTrapEnable OBJECT-TYPE
			SYNTAX AlarmEnable
			MAX-ACCESS read-write
			STATUS current
			DESCRIPTION
				"ASI OUT 1 - Selected input Trap Enable"
		::= { agw3000c01v2Entry 30 }

		-- 1.3.6.1.4.1.10106.3.101291.1.1.31
		agw3000c01v2IpOut1In OBJECT-TYPE
			SYNTAX GatewayInput3
			MAX-ACCESS read-write
			STATUS current
			DESCRIPTION
				"IP OUT 1 - Selected input"
		::= { agw3000c01v2Entry 31 }

		-- 1.3.6.1.4.1.10106.3.101291.1.1.32
		agw3000c01v2IpOut1InTrapEnable OBJECT-TYPE
			SYNTAX AlarmEnable
			MAX-ACCESS read-write
			STATUS current
			DESCRIPTION
				"IP OUT 1 - Selected input Trap Enable"
		::= { agw3000c01v2Entry 32 }

		-- 1.3.6.1.4.1.10106.3.101291.1.1.33
		agw3000c01v2IpOut2In OBJECT-TYPE
			SYNTAX GatewayInput3
			MAX-ACCESS read-write
			STATUS current
			DESCRIPTION
				"IP OUT 2 - Selected input"
		::= { agw3000c01v2Entry 33 }

		-- 1.3.6.1.4.1.10106.3.101291.1.1.34
		agw3000c01v2IpOut2InTrapEnable OBJECT-TYPE
			SYNTAX AlarmEnable
			MAX-ACCESS read-write
			STATUS current
			DESCRIPTION
				"IP OUT 2 - Selected input Trap Enable"
		::= { agw3000c01v2Entry 34 }

		-- 1.3.6.1.4.1.10106.3.101291.1.1.35
		agw3000c01v2PingEnable1 OBJECT-TYPE
			SYNTAX Bit0No1Yes
			MAX-ACCESS read-write
			STATUS current
			DESCRIPTION
				"Allows making a periodic ping to the unicast address"
		::= { agw3000c01v2Entry 35 }

		-- 1.3.6.1.4.1.10106.3.101291.1.1.37
		agw3000c01v2PingEnable2 OBJECT-TYPE
			SYNTAX Bit0No1Yes
			MAX-ACCESS read-write
			STATUS current
			DESCRIPTION
				"Allows making a periodic ping to the unicast address reserve"
		::= { agw3000c01v2Entry 37 }

		-- 1.3.6.1.4.1.10106.3.101291.1.1.39
		agw3000c01v2IpLinkFailEn OBJECT-TYPE
			SYNTAX Bit0No1Yes
			MAX-ACCESS read-write
			STATUS current
			DESCRIPTION
				"IP link lose signals fail in F_OUT GPO"
		::= { agw3000c01v2Entry 39 }

		-- 1.3.6.1.4.1.10106.3.101291.1.1.41
		agw3000c01v2IpDestFailEn OBJECT-TYPE
			SYNTAX Bit0No1Yes
			MAX-ACCESS read-write
			STATUS current
			DESCRIPTION
				"IP destination absence signals fail in F_OUT GPO"
		::= { agw3000c01v2Entry 41 }

		-- 1.3.6.1.4.1.10106.3.101291.1.1.43
		agw3000c01v2MaxTimeOut OBJECT-TYPE
			SYNTAX TimeX1Ms1
			MAX-ACCESS read-write
			STATUS current
			DESCRIPTION
				"Maximum time out for IP channels without receiving any packet.  It limits the low frequency jitter capacity."
		::= { agw3000c01v2Entry 43 }

		-- 1.3.6.1.4.1.10106.3.101291.1.1.45
		agw3000c01v2StatReset OBJECT-TYPE
			SYNTAX Bit0No1Yes
			MAX-ACCESS read-write
			STATUS current
			DESCRIPTION
				"Allows reseting the statistics measurements"
		::= { agw3000c01v2Entry 45 }

		-- 1.3.6.1.4.1.10106.3.101291.1.1.47
		agw3000c01v2StatSel OBJECT-TYPE
			SYNTAX Bit0Ipm1Ipr
			MAX-ACCESS read-write
			STATUS current
			DESCRIPTION
				"Allows selecting the channel to be displayed"
		::= { agw3000c01v2Entry 47 }

		-- 1.3.6.1.4.1.10106.3.101291.1.1.49
		agw3000c01v2StatMode OBJECT-TYPE
			SYNTAX Bit01s1Total
			MAX-ACCESS read-write
			STATUS current
			DESCRIPTION
				"Allows selecting the statistics mode"
		::= { agw3000c01v2Entry 49 }

		-- 1.3.6.1.4.1.10106.3.101291.1.1.51
		agw3000c01v2IgmpVersion OBJECT-TYPE
			SYNTAX Bit0V21V3
			MAX-ACCESS read-write
			STATUS current
			DESCRIPTION
				"Allows selecting the IGMP version"
		::= { agw3000c01v2Entry 51 }

		-- 1.3.6.1.4.1.10106.3.101291.1.1.53
		agw3000c01v2EthMode OBJECT-TYPE
			SYNTAX EthMode
			MAX-ACCESS read-write
			STATUS current
			DESCRIPTION
				"Allows selecting the Ethernet operating mode"
		::= { agw3000c01v2Entry 53 }

		-- 1.3.6.1.4.1.10106.3.101291.1.1.55
		agw3000c01v2SpeedForce OBJECT-TYPE
			SYNTAX Bit0Ann1For
			MAX-ACCESS read-write
			STATUS current
			DESCRIPTION
				"Allows selecting if the speed/mode is forced or announced for autonegotiation"
		::= { agw3000c01v2Entry 55 }

		-- 1.3.6.1.4.1.10106.3.101291.1.1.57
		agw3000c01v2PckDelAsiIn1 OBJECT-TYPE
			SYNTAX DelayPacket1
			MAX-ACCESS read-write
			STATUS current
			DESCRIPTION
				"Buffer size in packets for the ASI input 1"
		::= { agw3000c01v2Entry 57 }

		-- 1.3.6.1.4.1.10106.3.101291.1.1.59
		agw3000c01v2PckDelAsiIn2 OBJECT-TYPE
			SYNTAX DelayPacket1
			MAX-ACCESS read-write
			STATUS current
			DESCRIPTION
				"Buffer size in packets for the ASI input 2"
		::= { agw3000c01v2Entry 59 }

		-- 1.3.6.1.4.1.10106.3.101291.1.1.61
		agw3000c01v2PckDelIpIn1 OBJECT-TYPE
			SYNTAX DelayPacket1
			MAX-ACCESS read-write
			STATUS current
			DESCRIPTION
				"Buffer size in packets for the IP input 1"
		::= { agw3000c01v2Entry 61 }

		-- 1.3.6.1.4.1.10106.3.101291.1.1.63
		agw3000c01v2PckDelIpIn2 OBJECT-TYPE
			SYNTAX DelayPacket1
			MAX-ACCESS read-write
			STATUS current
			DESCRIPTION
				"Buffer size in packets for the IP input 2"
		::= { agw3000c01v2Entry 63 }

		-- 1.3.6.1.4.1.10106.3.101291.1.1.65
		agw3000c01v2AsiIn1Prior0 OBJECT-TYPE
			SYNTAX Uint2
			MAX-ACCESS read-write
			STATUS current
			DESCRIPTION
				"Allows selecting the ASI 1 input priority in output channel ASI OUT 1"
		::= { agw3000c01v2Entry 65 }

		-- 1.3.6.1.4.1.10106.3.101291.1.1.67
		agw3000c01v2AsiIn2Prior0 OBJECT-TYPE
			SYNTAX Uint2
			MAX-ACCESS read-write
			STATUS current
			DESCRIPTION
				"Allows selecting the ASI 2 input priority in output channel ASI OUT 1"
		::= { agw3000c01v2Entry 67 }

		-- 1.3.6.1.4.1.10106.3.101291.1.1.69
		agw3000c01v2IpIn1Prior0 OBJECT-TYPE
			SYNTAX Uint2
			MAX-ACCESS read-write
			STATUS current
			DESCRIPTION
				"Allows selecting the IP 1 input priority in output channel ASI OUT 1"
		::= { agw3000c01v2Entry 69 }

		-- 1.3.6.1.4.1.10106.3.101291.1.1.71
		agw3000c01v2IpIn2Prior0 OBJECT-TYPE
			SYNTAX Uint2
			MAX-ACCESS read-write
			STATUS current
			DESCRIPTION
				"Allows selecting the IP 2 input priority in output channel ASI OUT 1"
		::= { agw3000c01v2Entry 71 }

		-- 1.3.6.1.4.1.10106.3.101291.1.1.73
		agw3000c01v2AsiIn1Prior1 OBJECT-TYPE
			SYNTAX Uint2
			MAX-ACCESS read-write
			STATUS current
			DESCRIPTION
				"Allows selecting the ASI 1 input priority in output channel ASI OUT 2"
		::= { agw3000c01v2Entry 73 }

		-- 1.3.6.1.4.1.10106.3.101291.1.1.75
		agw3000c01v2AsiIn2Prior1 OBJECT-TYPE
			SYNTAX Uint2
			MAX-ACCESS read-write
			STATUS current
			DESCRIPTION
				"Allows selecting the ASI 2 input priority in output channel ASI OUT 2"
		::= { agw3000c01v2Entry 75 }

		-- 1.3.6.1.4.1.10106.3.101291.1.1.77
		agw3000c01v2IpIn1Prior1 OBJECT-TYPE
			SYNTAX Uint2
			MAX-ACCESS read-write
			STATUS current
			DESCRIPTION
				"Allows selecting the IP 1 input priority in output channel ASI OUT 2"
		::= { agw3000c01v2Entry 77 }

		-- 1.3.6.1.4.1.10106.3.101291.1.1.79
		agw3000c01v2IpIn2Prior1 OBJECT-TYPE
			SYNTAX Uint2
			MAX-ACCESS read-write
			STATUS current
			DESCRIPTION
				"Allows selecting the IP 2 input priority in output channel ASI OUT 2"
		::= { agw3000c01v2Entry 79 }

		-- 1.3.6.1.4.1.10106.3.101291.1.1.81
		agw3000c01v2AsiIn1Prior2 OBJECT-TYPE
			SYNTAX Uint2
			MAX-ACCESS read-write
			STATUS current
			DESCRIPTION
				"Allows selecting the ASI 1 input priority in output channel IP 1"
		::= { agw3000c01v2Entry 81 }

		-- 1.3.6.1.4.1.10106.3.101291.1.1.83
		agw3000c01v2AsiIn2Prior2 OBJECT-TYPE
			SYNTAX Uint2
			MAX-ACCESS read-write
			STATUS current
			DESCRIPTION
				"Allows selecting the ASI 2 input priority in output channel IP 1"
		::= { agw3000c01v2Entry 83 }

		-- 1.3.6.1.4.1.10106.3.101291.1.1.85
		agw3000c01v2IpIn1Prior2 OBJECT-TYPE
			SYNTAX Uint2
			MAX-ACCESS read-write
			STATUS current
			DESCRIPTION
				"Allows selecting the IP 1 input priority in output channel IP 1"
		::= { agw3000c01v2Entry 85 }

		-- 1.3.6.1.4.1.10106.3.101291.1.1.87
		agw3000c01v2IpIn2Prior2 OBJECT-TYPE
			SYNTAX Uint2
			MAX-ACCESS read-write
			STATUS current
			DESCRIPTION
				"Allows selecting the IP 2 input priority in output channel IP 1"
		::= { agw3000c01v2Entry 87 }

		-- 1.3.6.1.4.1.10106.3.101291.1.1.89
		agw3000c01v2AsiIn1Prior3 OBJECT-TYPE
			SYNTAX Uint2
			MAX-ACCESS read-write
			STATUS current
			DESCRIPTION
				"Allows selecting the ASI 1 input priority in output channel IP OUT 2"
		::= { agw3000c01v2Entry 89 }

		-- 1.3.6.1.4.1.10106.3.101291.1.1.91
		agw3000c01v2AsiIn2Prior3 OBJECT-TYPE
			SYNTAX Uint2
			MAX-ACCESS read-write
			STATUS current
			DESCRIPTION
				"Allows selecting the ASI 2 input priority in output channel IP OUT 2"
		::= { agw3000c01v2Entry 91 }

		-- 1.3.6.1.4.1.10106.3.101291.1.1.93
		agw3000c01v2IpIn1Prior3 OBJECT-TYPE
			SYNTAX Uint2
			MAX-ACCESS read-write
			STATUS current
			DESCRIPTION
				"Allows selecting the IP 1 input priority in output channel IP OUT 2"
		::= { agw3000c01v2Entry 93 }

		-- 1.3.6.1.4.1.10106.3.101291.1.1.95
		agw3000c01v2IpIn2Prior3 OBJECT-TYPE
			SYNTAX Uint2
			MAX-ACCESS read-write
			STATUS current
			DESCRIPTION
				"Allows selecting the IP 2 input priority in output channel IP OUT 2"
		::= { agw3000c01v2Entry 95 }

		-- 1.3.6.1.4.1.10106.3.101291.1.1.97
		agw3000c01v2ActivePreset OBJECT-TYPE
			SYNTAX Preset16Active
			MAX-ACCESS read-only
			STATUS current
			DESCRIPTION
				"Shows the active preset"
		::= { agw3000c01v2Entry 97 }

		-- 1.3.6.1.4.1.10106.3.101291.1.1.99
		agw3000c01v2LoadPreset OBJECT-TYPE
			SYNTAX Preset16Load
			MAX-ACCESS read-write
			STATUS current
			DESCRIPTION
				"Allows loading a preset"
		::= { agw3000c01v2Entry 99 }

		-- 1.3.6.1.4.1.10106.3.101291.1.1.101
		agw3000c01v2SavePreset OBJECT-TYPE
			SYNTAX Preset16Save
			MAX-ACCESS read-write
			STATUS current
			DESCRIPTION
				"Allows saving a preset"
		::= { agw3000c01v2Entry 101 }

		-- 1.3.6.1.4.1.10106.3.101291.1.1.103
		agw3000c01v2Str1UipDAdd3 OBJECT-TYPE
			SYNTAX Uint8
			MAX-ACCESS read-write
			STATUS current
			DESCRIPTION
				"Unicast IP address (3)"
		::= { agw3000c01v2Entry 103 }

		-- 1.3.6.1.4.1.10106.3.101291.1.1.105
		agw3000c01v2Str1UipDAdd2 OBJECT-TYPE
			SYNTAX Uint8
			MAX-ACCESS read-write
			STATUS current
			DESCRIPTION
				"Unicast IP address (2)"
		::= { agw3000c01v2Entry 105 }

		-- 1.3.6.1.4.1.10106.3.101291.1.1.107
		agw3000c01v2Str1UipDAdd1 OBJECT-TYPE
			SYNTAX Uint8
			MAX-ACCESS read-write
			STATUS current
			DESCRIPTION
				"Unicast IP address (1)"
		::= { agw3000c01v2Entry 107 }

		-- 1.3.6.1.4.1.10106.3.101291.1.1.109
		agw3000c01v2Str1UipDAdd0 OBJECT-TYPE
			SYNTAX Uint8
			MAX-ACCESS read-write
			STATUS current
			DESCRIPTION
				"Unicast IP address (0)"
		::= { agw3000c01v2Entry 109 }

		-- 1.3.6.1.4.1.10106.3.101291.1.1.111
		agw3000c01v2Str1MipDAdd3 OBJECT-TYPE
			SYNTAX Uint8
			MAX-ACCESS read-write
			STATUS current
			DESCRIPTION
				"Multicast IP address (3)"
		::= { agw3000c01v2Entry 111 }

		-- 1.3.6.1.4.1.10106.3.101291.1.1.113
		agw3000c01v2Str1MipDAdd2 OBJECT-TYPE
			SYNTAX Uint8
			MAX-ACCESS read-write
			STATUS current
			DESCRIPTION
				"Multicast IP address (2)"
		::= { agw3000c01v2Entry 113 }

		-- 1.3.6.1.4.1.10106.3.101291.1.1.115
		agw3000c01v2Str1MipDAdd1 OBJECT-TYPE
			SYNTAX Uint8
			MAX-ACCESS read-write
			STATUS current
			DESCRIPTION
				"Multicast IP address (1)"
		::= { agw3000c01v2Entry 115 }

		-- 1.3.6.1.4.1.10106.3.101291.1.1.117
		agw3000c01v2Str1MipDAdd0 OBJECT-TYPE
			SYNTAX Uint8
			MAX-ACCESS read-write
			STATUS current
			DESCRIPTION
				"Multicast IP address (0)"
		::= { agw3000c01v2Entry 117 }

		-- 1.3.6.1.4.1.10106.3.101291.1.1.119
		agw3000c01v2Str1DPort OBJECT-TYPE
			SYNTAX Uint16
			MAX-ACCESS read-write
			STATUS current
			DESCRIPTION
				"Destination port"
		::= { agw3000c01v2Entry 119 }

		-- 1.3.6.1.4.1.10106.3.101291.1.1.121
		agw3000c01v2Str1FecEna OBJECT-TYPE
			SYNTAX Bit0No1Yes
			MAX-ACCESS read-write
			STATUS current
			DESCRIPTION
				"Enable FEC"
		::= { agw3000c01v2Entry 121 }

		-- 1.3.6.1.4.1.10106.3.101291.1.1.123
		agw3000c01v2Str1MulticEna OBJECT-TYPE
			SYNTAX IpaTxMode
			MAX-ACCESS read-write
			STATUS current
			DESCRIPTION
				"RX mode"
		::= { agw3000c01v2Entry 123 }

		-- 1.3.6.1.4.1.10106.3.101291.1.1.125
		agw3000c01v2VlanRx1Enable OBJECT-TYPE
			SYNTAX Bit0No1Yes
			MAX-ACCESS read-write
			STATUS current
			DESCRIPTION
				"VLAN Enable"
		::= { agw3000c01v2Entry 125 }

		-- 1.3.6.1.4.1.10106.3.101291.1.1.127
		agw3000c01v2VlanRx1Id OBJECT-TYPE
			SYNTAX Uint12
			MAX-ACCESS read-write
			STATUS current
			DESCRIPTION
				"VLAN ID"
		::= { agw3000c01v2Entry 127 }

		-- 1.3.6.1.4.1.10106.3.101291.1.1.129
		agw3000c01v2Str2UipDAdd3 OBJECT-TYPE
			SYNTAX Uint8
			MAX-ACCESS read-write
			STATUS current
			DESCRIPTION
				"Unicast IP address (3)"
		::= { agw3000c01v2Entry 129 }

		-- 1.3.6.1.4.1.10106.3.101291.1.1.131
		agw3000c01v2Str2UipDAdd2 OBJECT-TYPE
			SYNTAX Uint8
			MAX-ACCESS read-write
			STATUS current
			DESCRIPTION
				"Unicast IP address (2)"
		::= { agw3000c01v2Entry 131 }

		-- 1.3.6.1.4.1.10106.3.101291.1.1.133
		agw3000c01v2Str2UipDAdd1 OBJECT-TYPE
			SYNTAX Uint8
			MAX-ACCESS read-write
			STATUS current
			DESCRIPTION
				"Unicast IP address (1)"
		::= { agw3000c01v2Entry 133 }

		-- 1.3.6.1.4.1.10106.3.101291.1.1.135
		agw3000c01v2Str2UipDAdd0 OBJECT-TYPE
			SYNTAX Uint8
			MAX-ACCESS read-write
			STATUS current
			DESCRIPTION
				"Unicast IP address (0)"
		::= { agw3000c01v2Entry 135 }

		-- 1.3.6.1.4.1.10106.3.101291.1.1.137
		agw3000c01v2Str2MipDAdd3 OBJECT-TYPE
			SYNTAX Uint8
			MAX-ACCESS read-write
			STATUS current
			DESCRIPTION
				"Multicast IP address (3)"
		::= { agw3000c01v2Entry 137 }

		-- 1.3.6.1.4.1.10106.3.101291.1.1.139
		agw3000c01v2Str2MipDAdd2 OBJECT-TYPE
			SYNTAX Uint8
			MAX-ACCESS read-write
			STATUS current
			DESCRIPTION
				"Multicast IP address (2)"
		::= { agw3000c01v2Entry 139 }

		-- 1.3.6.1.4.1.10106.3.101291.1.1.141
		agw3000c01v2Str2MipDAdd1 OBJECT-TYPE
			SYNTAX Uint8
			MAX-ACCESS read-write
			STATUS current
			DESCRIPTION
				"Multicast IP address (1)"
		::= { agw3000c01v2Entry 141 }

		-- 1.3.6.1.4.1.10106.3.101291.1.1.143
		agw3000c01v2Str2MipDAdd0 OBJECT-TYPE
			SYNTAX Uint8
			MAX-ACCESS read-write
			STATUS current
			DESCRIPTION
				"Multicast IP address (0)"
		::= { agw3000c01v2Entry 143 }

		-- 1.3.6.1.4.1.10106.3.101291.1.1.145
		agw3000c01v2Str2DPort OBJECT-TYPE
			SYNTAX Uint16
			MAX-ACCESS read-write
			STATUS current
			DESCRIPTION
				"Destination port"
		::= { agw3000c01v2Entry 145 }

		-- 1.3.6.1.4.1.10106.3.101291.1.1.147
		agw3000c01v2Str2FecEna OBJECT-TYPE
			SYNTAX Bit0No1Yes
			MAX-ACCESS read-write
			STATUS current
			DESCRIPTION
				"Enable FEC"
		::= { agw3000c01v2Entry 147 }

		-- 1.3.6.1.4.1.10106.3.101291.1.1.149
		agw3000c01v2Str2MulticEna OBJECT-TYPE
			SYNTAX IpaTxMode
			MAX-ACCESS read-write
			STATUS current
			DESCRIPTION
				"RX mode"
		::= { agw3000c01v2Entry 149 }

		-- 1.3.6.1.4.1.10106.3.101291.1.1.151
		agw3000c01v2VlanRx2Enable OBJECT-TYPE
			SYNTAX Bit0No1Yes
			MAX-ACCESS read-write
			STATUS current
			DESCRIPTION
				"VLAN Enable"
		::= { agw3000c01v2Entry 151 }

		-- 1.3.6.1.4.1.10106.3.101291.1.1.153
		agw3000c01v2VlanRx2Id OBJECT-TYPE
			SYNTAX Uint12
			MAX-ACCESS read-write
			STATUS current
			DESCRIPTION
				"VLAN ID"
		::= { agw3000c01v2Entry 153 }

		-- 1.3.6.1.4.1.10106.3.101291.1.1.155
		agw3000c01v2LocalIpAdd3 OBJECT-TYPE
			SYNTAX Uint8
			MAX-ACCESS read-write
			STATUS current
			DESCRIPTION
				"IP address (3)"
		::= { agw3000c01v2Entry 155 }

		-- 1.3.6.1.4.1.10106.3.101291.1.1.157
		agw3000c01v2LocalIpAdd2 OBJECT-TYPE
			SYNTAX Uint8
			MAX-ACCESS read-write
			STATUS current
			DESCRIPTION
				"IP address (2)"
		::= { agw3000c01v2Entry 157 }

		-- 1.3.6.1.4.1.10106.3.101291.1.1.159
		agw3000c01v2LocalIpAdd1 OBJECT-TYPE
			SYNTAX Uint8
			MAX-ACCESS read-write
			STATUS current
			DESCRIPTION
				"IP address (1)"
		::= { agw3000c01v2Entry 159 }

		-- 1.3.6.1.4.1.10106.3.101291.1.1.161
		agw3000c01v2LocalIpAdd0 OBJECT-TYPE
			SYNTAX Uint8
			MAX-ACCESS read-write
			STATUS current
			DESCRIPTION
				"IP address (0)"
		::= { agw3000c01v2Entry 161 }

		-- 1.3.6.1.4.1.10106.3.101291.1.1.163
		agw3000c01v2LocalIpMask3 OBJECT-TYPE
			SYNTAX Uint8
			MAX-ACCESS read-write
			STATUS current
			DESCRIPTION
				"IP mask (3)"
		::= { agw3000c01v2Entry 163 }

		-- 1.3.6.1.4.1.10106.3.101291.1.1.165
		agw3000c01v2LocalIpMask2 OBJECT-TYPE
			SYNTAX Uint8
			MAX-ACCESS read-write
			STATUS current
			DESCRIPTION
				"IP mask (2)"
		::= { agw3000c01v2Entry 165 }

		-- 1.3.6.1.4.1.10106.3.101291.1.1.167
		agw3000c01v2LocalIpMask1 OBJECT-TYPE
			SYNTAX Uint8
			MAX-ACCESS read-write
			STATUS current
			DESCRIPTION
				"IP mask (1)"
		::= { agw3000c01v2Entry 167 }

		-- 1.3.6.1.4.1.10106.3.101291.1.1.169
		agw3000c01v2LocalIpMask0 OBJECT-TYPE
			SYNTAX Uint8
			MAX-ACCESS read-write
			STATUS current
			DESCRIPTION
				"IP mask (0)"
		::= { agw3000c01v2Entry 169 }

		-- 1.3.6.1.4.1.10106.3.101291.1.1.171
		agw3000c01v2LocalIpGway3 OBJECT-TYPE
			SYNTAX Uint8
			MAX-ACCESS read-write
			STATUS current
			DESCRIPTION
				"Gateway IP address (3)"
		::= { agw3000c01v2Entry 171 }

		-- 1.3.6.1.4.1.10106.3.101291.1.1.173
		agw3000c01v2LocalIpGway2 OBJECT-TYPE
			SYNTAX Uint8
			MAX-ACCESS read-write
			STATUS current
			DESCRIPTION
				"Gateway IP address (2)"
		::= { agw3000c01v2Entry 173 }

		-- 1.3.6.1.4.1.10106.3.101291.1.1.175
		agw3000c01v2LocalIpGway1 OBJECT-TYPE
			SYNTAX Uint8
			MAX-ACCESS read-write
			STATUS current
			DESCRIPTION
				"Gateway IP address (1)"
		::= { agw3000c01v2Entry 175 }

		-- 1.3.6.1.4.1.10106.3.101291.1.1.177
		agw3000c01v2LocalIpGway0 OBJECT-TYPE
			SYNTAX Uint8
			MAX-ACCESS read-write
			STATUS current
			DESCRIPTION
				"Gateway IP address (0)"
		::= { agw3000c01v2Entry 177 }

		-- 1.3.6.1.4.1.10106.3.101291.1.1.179
		agw3000c01v2Tx1UniEna OBJECT-TYPE
			SYNTAX Bit0No1Yes
			MAX-ACCESS read-write
			STATUS current
			DESCRIPTION
				"Enable TX"
		::= { agw3000c01v2Entry 179 }

		-- 1.3.6.1.4.1.10106.3.101291.1.1.181
		agw3000c01v2Tx1MultiEna OBJECT-TYPE
			SYNTAX IpaTxMode
			MAX-ACCESS read-write
			STATUS current
			DESCRIPTION
				"TX mode"
		::= { agw3000c01v2Entry 181 }

		-- 1.3.6.1.4.1.10106.3.101291.1.1.183
		agw3000c01v2Tx1UipAdd3 OBJECT-TYPE
			SYNTAX Uint8
			MAX-ACCESS read-write
			STATUS current
			DESCRIPTION
				"Destination IP address (3)"
		::= { agw3000c01v2Entry 183 }

		-- 1.3.6.1.4.1.10106.3.101291.1.1.185
		agw3000c01v2Tx1UipAdd2 OBJECT-TYPE
			SYNTAX Uint8
			MAX-ACCESS read-write
			STATUS current
			DESCRIPTION
				"Destination IP address (2)"
		::= { agw3000c01v2Entry 185 }

		-- 1.3.6.1.4.1.10106.3.101291.1.1.187
		agw3000c01v2Tx1UipAdd1 OBJECT-TYPE
			SYNTAX Uint8
			MAX-ACCESS read-write
			STATUS current
			DESCRIPTION
				"Destination IP address (1)"
		::= { agw3000c01v2Entry 187 }

		-- 1.3.6.1.4.1.10106.3.101291.1.1.189
		agw3000c01v2Tx1UipAdd0 OBJECT-TYPE
			SYNTAX Uint8
			MAX-ACCESS read-write
			STATUS current
			DESCRIPTION
				"Destination IP address (0)"
		::= { agw3000c01v2Entry 189 }

		-- 1.3.6.1.4.1.10106.3.101291.1.1.191
		agw3000c01v2Tx1MipAdd3 OBJECT-TYPE
			SYNTAX Uint8
			MAX-ACCESS read-write
			STATUS current
			DESCRIPTION
				"Multicast dest. IP address (3)"
		::= { agw3000c01v2Entry 191 }

		-- 1.3.6.1.4.1.10106.3.101291.1.1.193
		agw3000c01v2Tx1MipAdd2 OBJECT-TYPE
			SYNTAX Uint8
			MAX-ACCESS read-write
			STATUS current
			DESCRIPTION
				"Multicast dest. IP address (2)"
		::= { agw3000c01v2Entry 193 }

		-- 1.3.6.1.4.1.10106.3.101291.1.1.195
		agw3000c01v2Tx1MipAdd1 OBJECT-TYPE
			SYNTAX Uint8
			MAX-ACCESS read-write
			STATUS current
			DESCRIPTION
				"Multicast dest. IP address (1)"
		::= { agw3000c01v2Entry 195 }

		-- 1.3.6.1.4.1.10106.3.101291.1.1.197
		agw3000c01v2Tx1MipAdd0 OBJECT-TYPE
			SYNTAX Uint8
			MAX-ACCESS read-write
			STATUS current
			DESCRIPTION
				"Multicast dest. IP address (0)"
		::= { agw3000c01v2Entry 197 }

		-- 1.3.6.1.4.1.10106.3.101291.1.1.199
		agw3000c01v2Tx1SPort OBJECT-TYPE
			SYNTAX Uint16
			MAX-ACCESS read-write
			STATUS current
			DESCRIPTION
				"Source port"
		::= { agw3000c01v2Entry 199 }

		-- 1.3.6.1.4.1.10106.3.101291.1.1.201
		agw3000c01v2Tx1DPort OBJECT-TYPE
			SYNTAX Uint16
			MAX-ACCESS read-write
			STATUS current
			DESCRIPTION
				"Destination port"
		::= { agw3000c01v2Entry 201 }

		-- 1.3.6.1.4.1.10106.3.101291.1.1.203
		agw3000c01v2VlanTxEnable1 OBJECT-TYPE
			SYNTAX Bit0No1Yes
			MAX-ACCESS read-write
			STATUS current
			DESCRIPTION
				"VLAN Enable"
		::= { agw3000c01v2Entry 203 }

		-- 1.3.6.1.4.1.10106.3.101291.1.1.205
		agw3000c01v2VlanTxPrior1 OBJECT-TYPE
			SYNTAX Uint3
			MAX-ACCESS read-write
			STATUS current
			DESCRIPTION
				"VLAN Priority"
		::= { agw3000c01v2Entry 205 }

		-- 1.3.6.1.4.1.10106.3.101291.1.1.207
		agw3000c01v2VlanTxId1 OBJECT-TYPE
			SYNTAX Uint12
			MAX-ACCESS read-write
			STATUS current
			DESCRIPTION
				"VLAN ID"
		::= { agw3000c01v2Entry 207 }

		-- 1.3.6.1.4.1.10106.3.101291.1.1.209
		agw3000c01v2Tx1LParam OBJECT-TYPE
			SYNTAX Uint5
			MAX-ACCESS read-write
			STATUS current
			DESCRIPTION
				"L parameter (FEC mode columns)"
		::= { agw3000c01v2Entry 209 }

		-- 1.3.6.1.4.1.10106.3.101291.1.1.211
		agw3000c01v2Tx1FecMode OBJECT-TYPE
			SYNTAX FecMode
			MAX-ACCESS read-write
			STATUS current
			DESCRIPTION
				"Protocol"
		::= { agw3000c01v2Entry 211 }

		-- 1.3.6.1.4.1.10106.3.101291.1.1.213
		agw3000c01v2Tx1DParam OBJECT-TYPE
			SYNTAX Uint5
			MAX-ACCESS read-write
			STATUS current
			DESCRIPTION
				"D parameter (FEC mode rows)"
		::= { agw3000c01v2Entry 213 }

		-- 1.3.6.1.4.1.10106.3.101291.1.1.215
		agw3000c01v2Tx1TspkInIppk OBJECT-TYPE
			SYNTAX Uint3
			MAX-ACCESS read-write
			STATUS current
			DESCRIPTION
				"TS packets in each IP packet"
		::= { agw3000c01v2Entry 215 }

		-- 1.3.6.1.4.1.10106.3.101291.1.1.217
		agw3000c01v2Tx1RowDelay OBJECT-TYPE
			SYNTAX Uint5
			MAX-ACCESS read-write
			STATUS current
			DESCRIPTION
				"FEC row delay"
		::= { agw3000c01v2Entry 217 }

		-- 1.3.6.1.4.1.10106.3.101291.1.1.219
		agw3000c01v2Tx1ColDelay OBJECT-TYPE
			SYNTAX Uint8
			MAX-ACCESS read-write
			STATUS current
			DESCRIPTION
				"FEC column delay"
		::= { agw3000c01v2Entry 219 }

		-- 1.3.6.1.4.1.10106.3.101291.1.1.221
		agw3000c01v2LowCost1 OBJECT-TYPE
			SYNTAX Bit0No1Yes
			MAX-ACCESS read-write
			STATUS current
			DESCRIPTION
				"TOS.  Low cost"
		::= { agw3000c01v2Entry 221 }

		-- 1.3.6.1.4.1.10106.3.101291.1.1.223
		agw3000c01v2HighReliab1 OBJECT-TYPE
			SYNTAX Bit0No1Yes
			MAX-ACCESS read-write
			STATUS current
			DESCRIPTION
				"TOS. High reliability"
		::= { agw3000c01v2Entry 223 }

		-- 1.3.6.1.4.1.10106.3.101291.1.1.225
		agw3000c01v2HighThroughp1 OBJECT-TYPE
			SYNTAX Bit0No1Yes
			MAX-ACCESS read-write
			STATUS current
			DESCRIPTION
				"TOS. High Throughput"
		::= { agw3000c01v2Entry 225 }

		-- 1.3.6.1.4.1.10106.3.101291.1.1.227
		agw3000c01v2LowDelay1 OBJECT-TYPE
			SYNTAX Bit0No1Yes
			MAX-ACCESS read-write
			STATUS current
			DESCRIPTION
				"TOS. Low delay"
		::= { agw3000c01v2Entry 227 }

		-- 1.3.6.1.4.1.10106.3.101291.1.1.229
		agw3000c01v2Precedence1 OBJECT-TYPE
			SYNTAX IpaPrecedence
			MAX-ACCESS read-write
			STATUS current
			DESCRIPTION
				"TOS. Precedence"
		::= { agw3000c01v2Entry 229 }

		-- 1.3.6.1.4.1.10106.3.101291.1.1.231
		agw3000c01v2Ttl1 OBJECT-TYPE
			SYNTAX Uint8
			MAX-ACCESS read-write
			STATUS current
			DESCRIPTION
				"Time to live"
		::= { agw3000c01v2Entry 231 }

		-- 1.3.6.1.4.1.10106.3.101291.1.1.233
		agw3000c01v2Str1IgmFAdd3 OBJECT-TYPE
			SYNTAX Uint8
			MAX-ACCESS read-write
			STATUS current
			DESCRIPTION
				"Source IP address (3)"
		::= { agw3000c01v2Entry 233 }

		-- 1.3.6.1.4.1.10106.3.101291.1.1.235
		agw3000c01v2Str1IgmFAdd2 OBJECT-TYPE
			SYNTAX Uint8
			MAX-ACCESS read-write
			STATUS current
			DESCRIPTION
				"Source IP address (2)"
		::= { agw3000c01v2Entry 235 }

		-- 1.3.6.1.4.1.10106.3.101291.1.1.237
		agw3000c01v2Str1IgmFAdd1 OBJECT-TYPE
			SYNTAX Uint8
			MAX-ACCESS read-write
			STATUS current
			DESCRIPTION
				"Source IP address (1)"
		::= { agw3000c01v2Entry 237 }

		-- 1.3.6.1.4.1.10106.3.101291.1.1.239
		agw3000c01v2Str1IgmFAdd0 OBJECT-TYPE
			SYNTAX Uint8
			MAX-ACCESS read-write
			STATUS current
			DESCRIPTION
				"Source IP address (0)"
		::= { agw3000c01v2Entry 239 }

		-- 1.3.6.1.4.1.10106.3.101291.1.1.241
		agw3000c01v2Str2IgmFAdd3 OBJECT-TYPE
			SYNTAX Uint8
			MAX-ACCESS read-write
			STATUS current
			DESCRIPTION
				"Source IP address (3)"
		::= { agw3000c01v2Entry 241 }

		-- 1.3.6.1.4.1.10106.3.101291.1.1.243
		agw3000c01v2Str2IgmFAdd2 OBJECT-TYPE
			SYNTAX Uint8
			MAX-ACCESS read-write
			STATUS current
			DESCRIPTION
				"Source IP address (2)"
		::= { agw3000c01v2Entry 243 }

		-- 1.3.6.1.4.1.10106.3.101291.1.1.245
		agw3000c01v2Str2IgmFAdd1 OBJECT-TYPE
			SYNTAX Uint8
			MAX-ACCESS read-write
			STATUS current
			DESCRIPTION
				"Source IP address (1)"
		::= { agw3000c01v2Entry 245 }

		-- 1.3.6.1.4.1.10106.3.101291.1.1.247
		agw3000c01v2Str2IgmFAdd0 OBJECT-TYPE
			SYNTAX Uint8
			MAX-ACCESS read-write
			STATUS current
			DESCRIPTION
				"Source IP address (0)"
		::= { agw3000c01v2Entry 247 }

		-- 1.3.6.1.4.1.10106.3.101291.1.1.249
		agw3000c01v2LocalIp2Add3 OBJECT-TYPE
			SYNTAX Uint8
			MAX-ACCESS read-write
			STATUS current
			DESCRIPTION
				"IP address (3)"
		::= { agw3000c01v2Entry 249 }

		-- 1.3.6.1.4.1.10106.3.101291.1.1.251
		agw3000c01v2LocalIp2Add2 OBJECT-TYPE
			SYNTAX Uint8
			MAX-ACCESS read-write
			STATUS current
			DESCRIPTION
				"IP address (2)"
		::= { agw3000c01v2Entry 251 }

		-- 1.3.6.1.4.1.10106.3.101291.1.1.253
		agw3000c01v2LocalIp2Add1 OBJECT-TYPE
			SYNTAX Uint8
			MAX-ACCESS read-write
			STATUS current
			DESCRIPTION
				"IP address (1)"
		::= { agw3000c01v2Entry 253 }

		-- 1.3.6.1.4.1.10106.3.101291.1.1.255
		agw3000c01v2LocalIp2Add0 OBJECT-TYPE
			SYNTAX Uint8
			MAX-ACCESS read-write
			STATUS current
			DESCRIPTION
				"IP address (0)"
		::= { agw3000c01v2Entry 255 }

		-- 1.3.6.1.4.1.10106.3.101291.1.1.257
		agw3000c01v2LocalIp2Msk3 OBJECT-TYPE
			SYNTAX Uint8
			MAX-ACCESS read-write
			STATUS current
			DESCRIPTION
				"IP mask (3)"
		::= { agw3000c01v2Entry 257 }

		-- 1.3.6.1.4.1.10106.3.101291.1.1.259
		agw3000c01v2LocalIp2Msk2 OBJECT-TYPE
			SYNTAX Uint8
			MAX-ACCESS read-write
			STATUS current
			DESCRIPTION
				"IP mask (2)"
		::= { agw3000c01v2Entry 259 }

		-- 1.3.6.1.4.1.10106.3.101291.1.1.261
		agw3000c01v2LocalIp2Msk1 OBJECT-TYPE
			SYNTAX Uint8
			MAX-ACCESS read-write
			STATUS current
			DESCRIPTION
				"IP mask (1)"
		::= { agw3000c01v2Entry 261 }

		-- 1.3.6.1.4.1.10106.3.101291.1.1.263
		agw3000c01v2LocalIp2Msk0 OBJECT-TYPE
			SYNTAX Uint8
			MAX-ACCESS read-write
			STATUS current
			DESCRIPTION
				"IP mask (0)"
		::= { agw3000c01v2Entry 263 }

		-- 1.3.6.1.4.1.10106.3.101291.1.1.265
		agw3000c01v2LocalIp2Gwy3 OBJECT-TYPE
			SYNTAX Uint8
			MAX-ACCESS read-write
			STATUS current
			DESCRIPTION
				"Gateway IP address (3)"
		::= { agw3000c01v2Entry 265 }

		-- 1.3.6.1.4.1.10106.3.101291.1.1.267
		agw3000c01v2LocalIp2Gwy2 OBJECT-TYPE
			SYNTAX Uint8
			MAX-ACCESS read-write
			STATUS current
			DESCRIPTION
				"Gateway IP address (2)"
		::= { agw3000c01v2Entry 267 }

		-- 1.3.6.1.4.1.10106.3.101291.1.1.269
		agw3000c01v2LocalIp2Gwy1 OBJECT-TYPE
			SYNTAX Uint8
			MAX-ACCESS read-write
			STATUS current
			DESCRIPTION
				"Gateway IP address (1)"
		::= { agw3000c01v2Entry 269 }

		-- 1.3.6.1.4.1.10106.3.101291.1.1.271
		agw3000c01v2LocalIp2Gwy0 OBJECT-TYPE
			SYNTAX Uint8
			MAX-ACCESS read-write
			STATUS current
			DESCRIPTION
				"Gateway IP address (0)"
		::= { agw3000c01v2Entry 271 }

		-- 1.3.6.1.4.1.10106.3.101291.1.1.273
		agw3000c01v2Tx2UniEna OBJECT-TYPE
			SYNTAX Bit0No1Yes
			MAX-ACCESS read-write
			STATUS current
			DESCRIPTION
				"Enable TX"
		::= { agw3000c01v2Entry 273 }

		-- 1.3.6.1.4.1.10106.3.101291.1.1.275
		agw3000c01v2Tx2MultiEna OBJECT-TYPE
			SYNTAX IpaTxMode
			MAX-ACCESS read-write
			STATUS current
			DESCRIPTION
				"TX mode"
		::= { agw3000c01v2Entry 275 }

		-- 1.3.6.1.4.1.10106.3.101291.1.1.277
		agw3000c01v2Tx2UipAdd3 OBJECT-TYPE
			SYNTAX Uint8
			MAX-ACCESS read-write
			STATUS current
			DESCRIPTION
				"Destination IP address (3)"
		::= { agw3000c01v2Entry 277 }

		-- 1.3.6.1.4.1.10106.3.101291.1.1.279
		agw3000c01v2Tx2UipAdd2 OBJECT-TYPE
			SYNTAX Uint8
			MAX-ACCESS read-write
			STATUS current
			DESCRIPTION
				"Destination IP address (2)"
		::= { agw3000c01v2Entry 279 }

		-- 1.3.6.1.4.1.10106.3.101291.1.1.281
		agw3000c01v2Tx2UipAdd1 OBJECT-TYPE
			SYNTAX Uint8
			MAX-ACCESS read-write
			STATUS current
			DESCRIPTION
				"Destination IP address (1)"
		::= { agw3000c01v2Entry 281 }

		-- 1.3.6.1.4.1.10106.3.101291.1.1.283
		agw3000c01v2Tx2UipAdd0 OBJECT-TYPE
			SYNTAX Uint8
			MAX-ACCESS read-write
			STATUS current
			DESCRIPTION
				"Destination IP address (0)"
		::= { agw3000c01v2Entry 283 }

		-- 1.3.6.1.4.1.10106.3.101291.1.1.285
		agw3000c01v2Tx2MipAdd3 OBJECT-TYPE
			SYNTAX Uint8
			MAX-ACCESS read-write
			STATUS current
			DESCRIPTION
				"Multicast dest. IP address (3)"
		::= { agw3000c01v2Entry 285 }

		-- 1.3.6.1.4.1.10106.3.101291.1.1.287
		agw3000c01v2Tx2MipAdd2 OBJECT-TYPE
			SYNTAX Uint8
			MAX-ACCESS read-write
			STATUS current
			DESCRIPTION
				"Multicast dest. IP address (2)"
		::= { agw3000c01v2Entry 287 }

		-- 1.3.6.1.4.1.10106.3.101291.1.1.289
		agw3000c01v2Tx2MipAdd1 OBJECT-TYPE
			SYNTAX Uint8
			MAX-ACCESS read-write
			STATUS current
			DESCRIPTION
				"Multicast dest. IP address (1)"
		::= { agw3000c01v2Entry 289 }

		-- 1.3.6.1.4.1.10106.3.101291.1.1.291
		agw3000c01v2Tx2MipAdd0 OBJECT-TYPE
			SYNTAX Uint8
			MAX-ACCESS read-write
			STATUS current
			DESCRIPTION
				"Multicast dest. IP address (0)"
		::= { agw3000c01v2Entry 291 }

		-- 1.3.6.1.4.1.10106.3.101291.1.1.293
		agw3000c01v2Tx2SPort OBJECT-TYPE
			SYNTAX Uint16
			MAX-ACCESS read-write
			STATUS current
			DESCRIPTION
				"Source port"
		::= { agw3000c01v2Entry 293 }

		-- 1.3.6.1.4.1.10106.3.101291.1.1.295
		agw3000c01v2Tx2DPort OBJECT-TYPE
			SYNTAX Uint16
			MAX-ACCESS read-write
			STATUS current
			DESCRIPTION
				"Destination port"
		::= { agw3000c01v2Entry 295 }

		-- 1.3.6.1.4.1.10106.3.101291.1.1.297
		agw3000c01v2VlanTxEnable2 OBJECT-TYPE
			SYNTAX Bit0No1Yes
			MAX-ACCESS read-write
			STATUS current
			DESCRIPTION
				"VLAN Enable"
		::= { agw3000c01v2Entry 297 }

		-- 1.3.6.1.4.1.10106.3.101291.1.1.299
		agw3000c01v2VlanTxPrior2 OBJECT-TYPE
			SYNTAX Uint3
			MAX-ACCESS read-write
			STATUS current
			DESCRIPTION
				"VLAN Priority"
		::= { agw3000c01v2Entry 299 }

		-- 1.3.6.1.4.1.10106.3.101291.1.1.301
		agw3000c01v2VlanTxId2 OBJECT-TYPE
			SYNTAX Uint12
			MAX-ACCESS read-write
			STATUS current
			DESCRIPTION
				"VLAN ID"
		::= { agw3000c01v2Entry 301 }

		-- 1.3.6.1.4.1.10106.3.101291.1.1.303
		agw3000c01v2Tx2LParam OBJECT-TYPE
			SYNTAX Uint5
			MAX-ACCESS read-write
			STATUS current
			DESCRIPTION
				"L parameter (FEC mode columns)"
		::= { agw3000c01v2Entry 303 }

		-- 1.3.6.1.4.1.10106.3.101291.1.1.305
		agw3000c01v2Tx2FecMode OBJECT-TYPE
			SYNTAX FecMode
			MAX-ACCESS read-write
			STATUS current
			DESCRIPTION
				"Protocol"
		::= { agw3000c01v2Entry 305 }

		-- 1.3.6.1.4.1.10106.3.101291.1.1.307
		agw3000c01v2Tx2DParam OBJECT-TYPE
			SYNTAX Uint5
			MAX-ACCESS read-write
			STATUS current
			DESCRIPTION
				"D parameter (FEC mode rows)"
		::= { agw3000c01v2Entry 307 }

		-- 1.3.6.1.4.1.10106.3.101291.1.1.309
		agw3000c01v2Tx2TspkInIppk OBJECT-TYPE
			SYNTAX Uint3
			MAX-ACCESS read-write
			STATUS current
			DESCRIPTION
				"TS packets in each IP packet"
		::= { agw3000c01v2Entry 309 }

		-- 1.3.6.1.4.1.10106.3.101291.1.1.311
		agw3000c01v2Tx2RowDelay OBJECT-TYPE
			SYNTAX Uint5
			MAX-ACCESS read-write
			STATUS current
			DESCRIPTION
				"FEC row delay"
		::= { agw3000c01v2Entry 311 }

		-- 1.3.6.1.4.1.10106.3.101291.1.1.313
		agw3000c01v2Tx2ColDelay OBJECT-TYPE
			SYNTAX Uint8
			MAX-ACCESS read-write
			STATUS current
			DESCRIPTION
				"FEC column delay"
		::= { agw3000c01v2Entry 313 }

		-- 1.3.6.1.4.1.10106.3.101291.1.1.315
		agw3000c01v2LowCost2 OBJECT-TYPE
			SYNTAX Bit0No1Yes
			MAX-ACCESS read-write
			STATUS current
			DESCRIPTION
				"TOS.  Low cost"
		::= { agw3000c01v2Entry 315 }

		-- 1.3.6.1.4.1.10106.3.101291.1.1.317
		agw3000c01v2HighReliab2 OBJECT-TYPE
			SYNTAX Bit0No1Yes
			MAX-ACCESS read-write
			STATUS current
			DESCRIPTION
				"TOS. High reliability"
		::= { agw3000c01v2Entry 317 }

		-- 1.3.6.1.4.1.10106.3.101291.1.1.319
		agw3000c01v2HighThroughp2 OBJECT-TYPE
			SYNTAX Bit0No1Yes
			MAX-ACCESS read-write
			STATUS current
			DESCRIPTION
				"TOS. High Throughput"
		::= { agw3000c01v2Entry 319 }

		-- 1.3.6.1.4.1.10106.3.101291.1.1.321
		agw3000c01v2LowDelay2 OBJECT-TYPE
			SYNTAX Bit0No1Yes
			MAX-ACCESS read-write
			STATUS current
			DESCRIPTION
				"TOS. Low delay"
		::= { agw3000c01v2Entry 321 }

		-- 1.3.6.1.4.1.10106.3.101291.1.1.323
		agw3000c01v2Precedence2 OBJECT-TYPE
			SYNTAX IpaPrecedence
			MAX-ACCESS read-write
			STATUS current
			DESCRIPTION
				"TOS. Precedence"
		::= { agw3000c01v2Entry 323 }

		-- 1.3.6.1.4.1.10106.3.101291.1.1.325
		agw3000c01v2Ttl2 OBJECT-TYPE
			SYNTAX Uint8
			MAX-ACCESS read-write
			STATUS current
			DESCRIPTION
				"Time to live"
		::= { agw3000c01v2Entry 325 }

		-- 1.3.6.1.4.1.10106.3.101291.1.1.327
		agw3000c01v2Test0 OBJECT-TYPE
			SYNTAX Uint8
			MAX-ACCESS read-write
			STATUS current
			DESCRIPTION
				"Test 0"
		::= { agw3000c01v2Entry 327 }

		-- 1.3.6.1.4.1.10106.3.101291.1.1.329
		agw3000c01v2Test1 OBJECT-TYPE
			SYNTAX Uint8
			MAX-ACCESS read-write
			STATUS current
			DESCRIPTION
				"Test 1"
		::= { agw3000c01v2Entry 329 }

		-- 1.3.6.1.4.1.10106.3.101291.1.1.331
		agw3000c01v2Test2 OBJECT-TYPE
			SYNTAX Uint8
			MAX-ACCESS read-write
			STATUS current
			DESCRIPTION
				"Test 2"
		::= { agw3000c01v2Entry 331 }

		-- 1.3.6.1.4.1.10106.3.101291.1.1.333
		agw3000c01v2Test3 OBJECT-TYPE
			SYNTAX Uint8
			MAX-ACCESS read-write
			STATUS current
			DESCRIPTION
				"Test 3"
		::= { agw3000c01v2Entry 333 }

		-- 1.3.6.1.4.1.10106.3.101291.1.1.335
		agw3000c01v2Test4 OBJECT-TYPE
			SYNTAX Uint8
			MAX-ACCESS read-write
			STATUS current
			DESCRIPTION
				"Test 4"
		::= { agw3000c01v2Entry 335 }

		-- 1.3.6.1.4.1.10106.3.101291.1.1.337
		agw3000c01v2Test5 OBJECT-TYPE
			SYNTAX Uint8
			MAX-ACCESS read-write
			STATUS current
			DESCRIPTION
				"Test 5"
		::= { agw3000c01v2Entry 337 }

		-- 1.3.6.1.4.1.10106.3.101291.1.1.339
		agw3000c01v2AsiOut1Fail OBJECT-TYPE
			SYNTAX BitFail
			MAX-ACCESS read-only
			STATUS current
			DESCRIPTION
				"The ASI 1 output signal is not valid because all inputs failed"
		::= { agw3000c01v2Entry 339 }

		-- 1.3.6.1.4.1.10106.3.101291.1.1.341
		agw3000c01v2AsiOut2Fail OBJECT-TYPE
			SYNTAX BitFail
			MAX-ACCESS read-only
			STATUS current
			DESCRIPTION
				"The ASI 2 output signal is not valid because all inputs failed"
		::= { agw3000c01v2Entry 341 }

		-- 1.3.6.1.4.1.10106.3.101291.1.1.343
		agw3000c01v2IpOut1Fail OBJECT-TYPE
			SYNTAX BitFail
			MAX-ACCESS read-only
			STATUS current
			DESCRIPTION
				"The IP 1 output signal is not valid because all inputs failed"
		::= { agw3000c01v2Entry 343 }

		-- 1.3.6.1.4.1.10106.3.101291.1.1.345
		agw3000c01v2IpOut2Fail OBJECT-TYPE
			SYNTAX BitFail
			MAX-ACCESS read-only
			STATUS current
			DESCRIPTION
				"The IP 2 output signal is not valid because all inputs failed"
		::= { agw3000c01v2Entry 345 }

		-- 1.3.6.1.4.1.10106.3.101291.1.1.347
		agw3000c01v2AsiIn1Fail OBJECT-TYPE
			SYNTAX BitFail
			MAX-ACCESS read-only
			STATUS current
			DESCRIPTION
				"ASI IN 1 fail status"
		::= { agw3000c01v2Entry 347 }

		-- 1.3.6.1.4.1.10106.3.101291.1.1.348
		agw3000c01v2AsiIn1FailTrapEnable OBJECT-TYPE
			SYNTAX AlarmEnable
			MAX-ACCESS read-write
			STATUS current
			DESCRIPTION
				"ASI IN 1 fail status Trap Enable"
		::= { agw3000c01v2Entry 348 }

		-- 1.3.6.1.4.1.10106.3.101291.1.1.349
		agw3000c01v2ExAsiIn1Fail OBJECT-TYPE
			SYNTAX BitFail
			MAX-ACCESS read-only
			STATUS current
			DESCRIPTION
				"ASI IN 1 external input fail status"
		::= { agw3000c01v2Entry 349 }

		-- 1.3.6.1.4.1.10106.3.101291.1.1.350
		agw3000c01v2ExAsiIn1FailTrapEnable OBJECT-TYPE
			SYNTAX AlarmEnable
			MAX-ACCESS read-write
			STATUS current
			DESCRIPTION
				"ASI IN 1 external input fail status Trap Enable"
		::= { agw3000c01v2Entry 350 }

		-- 1.3.6.1.4.1.10106.3.101291.1.1.351
		agw3000c01v2AsiIn2Fail OBJECT-TYPE
			SYNTAX BitFail
			MAX-ACCESS read-only
			STATUS current
			DESCRIPTION
				"ASI  IN 2 fail status"
		::= { agw3000c01v2Entry 351 }

		-- 1.3.6.1.4.1.10106.3.101291.1.1.352
		agw3000c01v2AsiIn2FailTrapEnable OBJECT-TYPE
			SYNTAX AlarmEnable
			MAX-ACCESS read-write
			STATUS current
			DESCRIPTION
				"ASI  IN 2 fail status Trap Enable"
		::= { agw3000c01v2Entry 352 }

		-- 1.3.6.1.4.1.10106.3.101291.1.1.353
		agw3000c01v2ExAsiIn2Fail OBJECT-TYPE
			SYNTAX BitFail
			MAX-ACCESS read-only
			STATUS current
			DESCRIPTION
				"ASI  IN 2 fail external input fail status"
		::= { agw3000c01v2Entry 353 }

		-- 1.3.6.1.4.1.10106.3.101291.1.1.354
		agw3000c01v2ExAsiIn2FailTrapEnable OBJECT-TYPE
			SYNTAX AlarmEnable
			MAX-ACCESS read-write
			STATUS current
			DESCRIPTION
				"ASI  IN 2 fail external input fail status Trap Enable"
		::= { agw3000c01v2Entry 354 }

		-- 1.3.6.1.4.1.10106.3.101291.1.1.355
		agw3000c01v2IpIn1Fail OBJECT-TYPE
			SYNTAX BitFail
			MAX-ACCESS read-only
			STATUS current
			DESCRIPTION
				"IP IN 1 fail status"
		::= { agw3000c01v2Entry 355 }

		-- 1.3.6.1.4.1.10106.3.101291.1.1.356
		agw3000c01v2IpIn1FailTrapEnable OBJECT-TYPE
			SYNTAX AlarmEnable
			MAX-ACCESS read-write
			STATUS current
			DESCRIPTION
				"IP IN 1 fail status Trap Enable"
		::= { agw3000c01v2Entry 356 }

		-- 1.3.6.1.4.1.10106.3.101291.1.1.357
		agw3000c01v2ExIpIn1Fail OBJECT-TYPE
			SYNTAX BitFail
			MAX-ACCESS read-only
			STATUS current
			DESCRIPTION
				"IP IN 1 external input fail status"
		::= { agw3000c01v2Entry 357 }

		-- 1.3.6.1.4.1.10106.3.101291.1.1.358
		agw3000c01v2ExIpIn1FailTrapEnable OBJECT-TYPE
			SYNTAX AlarmEnable
			MAX-ACCESS read-write
			STATUS current
			DESCRIPTION
				"IP IN 1 external input fail status Trap Enable"
		::= { agw3000c01v2Entry 358 }

		-- 1.3.6.1.4.1.10106.3.101291.1.1.359
		agw3000c01v2IpIn2Fail OBJECT-TYPE
			SYNTAX BitFail
			MAX-ACCESS read-only
			STATUS current
			DESCRIPTION
				"IP IN 2 input status"
		::= { agw3000c01v2Entry 359 }

		-- 1.3.6.1.4.1.10106.3.101291.1.1.360
		agw3000c01v2IpIn2FailTrapEnable OBJECT-TYPE
			SYNTAX AlarmEnable
			MAX-ACCESS read-write
			STATUS current
			DESCRIPTION
				"IP IN 2 input status Trap Enable"
		::= { agw3000c01v2Entry 360 }

		-- 1.3.6.1.4.1.10106.3.101291.1.1.361
		agw3000c01v2ExIpIn2Fail OBJECT-TYPE
			SYNTAX BitFail
			MAX-ACCESS read-only
			STATUS current
			DESCRIPTION
				"IP IN 2 external input fail status"
		::= { agw3000c01v2Entry 361 }

		-- 1.3.6.1.4.1.10106.3.101291.1.1.362
		agw3000c01v2ExIpIn2FailTrapEnable OBJECT-TYPE
			SYNTAX AlarmEnable
			MAX-ACCESS read-write
			STATUS current
			DESCRIPTION
				"IP IN 2 external input fail status Trap Enable"
		::= { agw3000c01v2Entry 362 }

		-- 1.3.6.1.4.1.10106.3.101291.1.1.363
		agw3000c01v2DestAvailable1 OBJECT-TYPE
			SYNTAX Bit0No1Yes
			MAX-ACCESS read-only
			STATUS current
			DESCRIPTION
				"Destination IP available"
		::= { agw3000c01v2Entry 363 }

		-- 1.3.6.1.4.1.10106.3.101291.1.1.365
		agw3000c01v2DestAvailable2 OBJECT-TYPE
			SYNTAX Bit0No1Yes
			MAX-ACCESS read-only
			STATUS current
			DESCRIPTION
				"Destination IP available"
		::= { agw3000c01v2Entry 365 }

		-- 1.3.6.1.4.1.10106.3.101291.1.1.367
		agw3000c01v2BlindModStat1 OBJECT-TYPE
			SYNTAX BlindModeStat
			MAX-ACCESS read-only
			STATUS current
			DESCRIPTION
				"Active receiver in blind mode"
		::= { agw3000c01v2Entry 367 }

		-- 1.3.6.1.4.1.10106.3.101291.1.1.369
		agw3000c01v2BlindModStat2 OBJECT-TYPE
			SYNTAX BlindModeStat
			MAX-ACCESS read-only
			STATUS current
			DESCRIPTION
				"Active receiver in blind mode"
		::= { agw3000c01v2Entry 369 }

		-- 1.3.6.1.4.1.10106.3.101291.1.1.371
		agw3000c01v2AsiIn1Delay OBJECT-TYPE
			SYNTAX DelayX131Ms
			MAX-ACCESS read-only
			STATUS current
			DESCRIPTION
				"ASI IN 1 to output delay"
		::= { agw3000c01v2Entry 371 }

		-- 1.3.6.1.4.1.10106.3.101291.1.1.373
		agw3000c01v2AsiIn2Delay OBJECT-TYPE
			SYNTAX DelayX131Ms
			MAX-ACCESS read-only
			STATUS current
			DESCRIPTION
				"ASI IN 2 to output delay"
		::= { agw3000c01v2Entry 373 }

		-- 1.3.6.1.4.1.10106.3.101291.1.1.375
		agw3000c01v2IpIn1Delay OBJECT-TYPE
			SYNTAX DelayX131Ms
			MAX-ACCESS read-only
			STATUS current
			DESCRIPTION
				"IP IN 1 to output delay"
		::= { agw3000c01v2Entry 375 }

		-- 1.3.6.1.4.1.10106.3.101291.1.1.377
		agw3000c01v2IpIn2Delay OBJECT-TYPE
			SYNTAX DelayX131Ms
			MAX-ACCESS read-only
			STATUS current
			DESCRIPTION
				"IP IN 2 to output delay"
		::= { agw3000c01v2Entry 377 }

		-- 1.3.6.1.4.1.10106.3.101291.1.1.379
		agw3000c01v2IpRxAddress3 OBJECT-TYPE
			SYNTAX Uint8
			MAX-ACCESS read-only
			STATUS current
			DESCRIPTION
				"RX packets source IP address (3)"
		::= { agw3000c01v2Entry 379 }

		-- 1.3.6.1.4.1.10106.3.101291.1.1.381
		agw3000c01v2IpRxAddress2 OBJECT-TYPE
			SYNTAX Uint8
			MAX-ACCESS read-only
			STATUS current
			DESCRIPTION
				"RX packets source IP address (2)"
		::= { agw3000c01v2Entry 381 }

		-- 1.3.6.1.4.1.10106.3.101291.1.1.383
		agw3000c01v2IpRxAddress1 OBJECT-TYPE
			SYNTAX Uint8
			MAX-ACCESS read-only
			STATUS current
			DESCRIPTION
				"RX packets source IP address (1)"
		::= { agw3000c01v2Entry 383 }

		-- 1.3.6.1.4.1.10106.3.101291.1.1.385
		agw3000c01v2IpRxAddress0 OBJECT-TYPE
			SYNTAX Uint8
			MAX-ACCESS read-only
			STATUS current
			DESCRIPTION
				"RX packets source IP address (0)"
		::= { agw3000c01v2Entry 385 }

		-- 1.3.6.1.4.1.10106.3.101291.1.1.387
		agw3000c01v2IpRxPort OBJECT-TYPE
			SYNTAX Uint16
			MAX-ACCESS read-only
			STATUS current
			DESCRIPTION
				"RX packets UDP source port"
		::= { agw3000c01v2Entry 387 }

		-- 1.3.6.1.4.1.10106.3.101291.1.1.389
		agw3000c01v2LParam OBJECT-TYPE
			SYNTAX Uint5
			MAX-ACCESS read-only
			STATUS current
			DESCRIPTION
				"L parameter (FEC mode columns)"
		::= { agw3000c01v2Entry 389 }

		-- 1.3.6.1.4.1.10106.3.101291.1.1.391
		agw3000c01v2FecMode OBJECT-TYPE
			SYNTAX FecMode
			MAX-ACCESS read-only
			STATUS current
			DESCRIPTION
				"Protocol"
		::= { agw3000c01v2Entry 391 }

		-- 1.3.6.1.4.1.10106.3.101291.1.1.393
		agw3000c01v2PacketSize OBJECT-TYPE
			SYNTAX Bit02041188
			MAX-ACCESS read-only
			STATUS current
			DESCRIPTION
				"Bytes in TS packets"
		::= { agw3000c01v2Entry 393 }

		-- 1.3.6.1.4.1.10106.3.101291.1.1.395
		agw3000c01v2DParam OBJECT-TYPE
			SYNTAX Uint5
			MAX-ACCESS read-only
			STATUS current
			DESCRIPTION
				"D parameter (FEC mode rows)"
		::= { agw3000c01v2Entry 395 }

		-- 1.3.6.1.4.1.10106.3.101291.1.1.397
		agw3000c01v2TsPckInIpPck OBJECT-TYPE
			SYNTAX Uint3
			MAX-ACCESS read-only
			STATUS current
			DESCRIPTION
				"TS packets in each IP packet"
		::= { agw3000c01v2Entry 397 }

		-- 1.3.6.1.4.1.10106.3.101291.1.1.399
		agw3000c01v2PacketRate OBJECT-TYPE
			SYNTAX PacketRate
			MAX-ACCESS read-only
			STATUS current
			DESCRIPTION
				"IP packet rate"
		::= { agw3000c01v2Entry 399 }

		-- 1.3.6.1.4.1.10106.3.101291.1.1.401
		agw3000c01v2TimeSinceReset OBJECT-TYPE
			SYNTAX TimeS4
			MAX-ACCESS read-only
			STATUS current
			DESCRIPTION
				"Elapsed time from last reset"
		::= { agw3000c01v2Entry 401 }

		-- 1.3.6.1.4.1.10106.3.101291.1.1.403
		agw3000c01v2LostIpPck OBJECT-TYPE
			SYNTAX Uint16
			MAX-ACCESS read-only
			STATUS current
			DESCRIPTION
				"Lost IP packets"
		::= { agw3000c01v2Entry 403 }

		-- 1.3.6.1.4.1.10106.3.101291.1.1.405
		agw3000c01v2RecoveredIpPck OBJECT-TYPE
			SYNTAX Uint16
			MAX-ACCESS read-only
			STATUS current
			DESCRIPTION
				"Recovered IP packets"
		::= { agw3000c01v2Entry 405 }

		-- 1.3.6.1.4.1.10106.3.101291.1.1.407
		agw3000c01v2BadCrcPck OBJECT-TYPE
			SYNTAX Uint16
			MAX-ACCESS read-only
			STATUS current
			DESCRIPTION
				"Bad CRC packets"
		::= { agw3000c01v2Entry 407 }

		-- 1.3.6.1.4.1.10106.3.101291.1.1.409
		agw3000c01v2OutOrdIpPck OBJECT-TYPE
			SYNTAX Uint16
			MAX-ACCESS read-only
			STATUS current
			DESCRIPTION
				"Out of order IP packets"
		::= { agw3000c01v2Entry 409 }

		-- 1.3.6.1.4.1.10106.3.101291.1.1.411
		agw3000c01v2FecRate OBJECT-TYPE
			SYNTAX PacketRate
			MAX-ACCESS read-only
			STATUS current
			DESCRIPTION
				"FEC packet rate"
		::= { agw3000c01v2Entry 411 }

		-- 1.3.6.1.4.1.10106.3.101291.1.1.413
		agw3000c01v2Link OBJECT-TYPE
			SYNTAX IpaEtherStat
			MAX-ACCESS read-only
			STATUS current
			DESCRIPTION
				"Ethernet conection status"
		::= { agw3000c01v2Entry 413 }

		-- 1.3.6.1.4.1.10106.3.101291.1.1.415
		agw3000c01v2BufferStatus OBJECT-TYPE
			SYNTAX Rate1
			MAX-ACCESS read-only
			STATUS current
			DESCRIPTION
				"Buffer filling status in non DVB-T mode"
		::= { agw3000c01v2Entry 415 }

		-- 1.3.6.1.4.1.10106.3.101291.1.1.417
		agw3000c01v2PingStatus1 OBJECT-TYPE
			SYNTAX IpaPingStat
			MAX-ACCESS read-only
			STATUS current
			DESCRIPTION
				"Ping status"
		::= { agw3000c01v2Entry 417 }

		-- 1.3.6.1.4.1.10106.3.101291.1.1.419
		agw3000c01v2PingStatus2 OBJECT-TYPE
			SYNTAX IpaPingStat
			MAX-ACCESS read-only
			STATUS current
			DESCRIPTION
				"Ping status"
		::= { agw3000c01v2Entry 419 }

		-- 1.3.6.1.4.1.10106.3.101291.1.1.421
		agw3000c01v2SerialNo OBJECT-TYPE
			SYNTAX SerialNo
			MAX-ACCESS read-only
			STATUS current
			DESCRIPTION
				"Serial number"
		::= { agw3000c01v2Entry 421 }

		-- 1.3.6.1.4.1.10106.3.101291.1.1.423
		agw3000c01v2MaxDelayTxIp OBJECT-TYPE
			SYNTAX TimeX10Ms
			MAX-ACCESS read-write
			STATUS current
			DESCRIPTION
				"Time before starting to transmit after recovering signal"
		::= { agw3000c01v2Entry 423 }

		-- 1.3.6.1.4.1.10106.3.101291.1.1.425
		agw3000c01v2InpFailMode OBJECT-TYPE
			SYNTAX Bit0Yes1No
			MAX-ACCESS read-write
			STATUS current
			DESCRIPTION
				"Selects if the output is muted when all the inputs fail"
		::= { agw3000c01v2Entry 425 }

		-- 1.3.6.1.4.1.10106.3.407601
		ham3000c02v1 OBJECT IDENTIFIER ::= { albalaProducts 407601 }

		-- 1.3.6.1.4.1.10106.3.407601.1
		ham3000c02v1Table  OBJECT-TYPE
			SYNTAX SEQUENCE OF Ham3000c02v1Entry
			MAX-ACCESS not-accessible
			STATUS current
			DESCRIPTION
				"Module  HAM3000C02V1 Table"
			::= { ham3000c02v1 1 }

		-- 1.3.6.1.4.1.10106.3.407601.1.1
		ham3000c02v1Entry  OBJECT-TYPE
			SYNTAX Ham3000c02v1Entry
			MAX-ACCESS not-accessible
			STATUS current
			DESCRIPTION
				"Module HAM3000C02V1 Entry"
			INDEX { ham3000c02v1Index }
			::= { ham3000c02v1Table 1 }

			Ham3000c02v1Entry ::=
			SEQUENCE {
				ham3000c02v1Index
				ModuleIndex,
				ham3000c02v1ActivePreset
				Preset16Active,
				ham3000c02v1LoadPreset
				Preset16Load,
				ham3000c02v1SynchroMode
				Bit0Fra1Lin,
				ham3000c02v1FailMode
				Bit0Fre1Blk,
				ham3000c02v1DelayMode
				Bit0Syn1De2,
				ham3000c02v1HDelay
				DelayPixel5,
				ham3000c02v1FrameDelay
				DelayFram5,
				ham3000c02v1VDelay
				DelayLines2,
				ham3000c02v1MuxAuxC1
				AudioMxInput6,
				ham3000c02v1MuxAuxC2
				AudioMxInput6,
				ham3000c02v1MuxAuxC3
				AudioMxInput6,
				ham3000c02v1MuxAuxC4
				AudioMxInput6,
				ham3000c02v1FullScaleLev
				LevelDbu,
				ham3000c02v1OvldLevel
				LevelDbfs4,
				ham3000c02v1SilenceLevel
				LevelDbfs3,
				ham3000c02v1SilenceTime
				TimeS2,
				ham3000c02v1Gen1PipsTone
				Bit0Pips1Wav,
				ham3000c02v1Gen2PipsTone
				Bit0Pips1Wav,
				ham3000c02v1MediasGen1
				BitMask,
				ham3000c02v1MediasGen2
				BitMask,
				ham3000c02v1FreqPips1
				FrqGen,
				ham3000c02v1FreqPips2
				FrqGen,
				ham3000c02v1LevelPips1
				LevelDbfsD,
				ham3000c02v1LevelPips2
				LevelDbfsD,
				ham3000c02v1NPipsHour
				Uint4,
				ham3000c02v1NPipsHalf
				Uint4,
				ham3000c02v1ShortPerHour
				TimeX100Ms,
				ham3000c02v1ShortPerHalf
				TimeX100Ms,
				ham3000c02v1LongPerHour
				TimeX100Ms,
				ham3000c02v1LongPerHalf
				TimeX100Ms,
				ham3000c02v1EmbG1p0l
				AudioMxInputB,
				ham3000c02v1EmbG1p0lMonPh
				Bit0Nor1Inv,
				ham3000c02v1EmbG1p0lMono
				BitMask,
				ham3000c02v1EmbG1p0r
				AudioMxInputB,
				ham3000c02v1EmbG1p0rMonPh
				Bit0Nor1Inv,
				ham3000c02v1EmbG1p0rMono
				BitMask,
				ham3000c02v1EmbG1p1l
				AudioMxInputB,
				ham3000c02v1EmbG1p1lMonPh
				Bit0Nor1Inv,
				ham3000c02v1EmbG1p1lMono
				BitMask,
				ham3000c02v1EmbG1p1r
				AudioMxInputB,
				ham3000c02v1EmbG1p1rMonPh
				Bit0Nor1Inv,
				ham3000c02v1EmbG1p1rMono
				BitMask,
				ham3000c02v1EmbG2p0l
				AudioMxInputB,
				ham3000c02v1EmbG2p0lMonPh
				Bit0Nor1Inv,
				ham3000c02v1EmbG2p0lMono
				BitMask,
				ham3000c02v1EmbG2p0r
				AudioMxInputB,
				ham3000c02v1EmbG2p0rMonPh
				Bit0Nor1Inv,
				ham3000c02v1EmbG2p0rMono
				BitMask,
				ham3000c02v1EmbG2p1l
				AudioMxInputB,
				ham3000c02v1EmbG2p1lMonPh
				Bit0Nor1Inv,
				ham3000c02v1EmbG2p1lMono
				BitMask,
				ham3000c02v1EmbG2p1r
				AudioMxInputB,
				ham3000c02v1EmbG2p1rMonPh
				Bit0Nor1Inv,
				ham3000c02v1EmbG2p1rMono
				BitMask,
				ham3000c02v1EmbG3p0l
				AudioMxInputB,
				ham3000c02v1EmbG3p0lMonPh
				Bit0Nor1Inv,
				ham3000c02v1EmbG3p0lMono
				BitMask,
				ham3000c02v1EmbG3p0r
				AudioMxInputB,
				ham3000c02v1EmbG3p0rMonPh
				Bit0Nor1Inv,
				ham3000c02v1EmbG3p0rMono
				BitMask,
				ham3000c02v1EmbG3p1l
				AudioMxInputB,
				ham3000c02v1EmbG3p1lMonPh
				Bit0Nor1Inv,
				ham3000c02v1EmbG3p1lMono
				BitMask,
				ham3000c02v1EmbG3p1r
				AudioMxInputB,
				ham3000c02v1EmbG3p1rMonPh
				Bit0Nor1Inv,
				ham3000c02v1EmbG3p1rMono
				BitMask,
				ham3000c02v1EmbG4p0l
				AudioMxInputB,
				ham3000c02v1EmbG4p0lMonPh
				Bit0Nor1Inv,
				ham3000c02v1EmbG4p0lMono
				BitMask,
				ham3000c02v1EmbG4p0r
				AudioMxInputB,
				ham3000c02v1EmbG4p0rMonPh
				Bit0Nor1Inv,
				ham3000c02v1EmbG4p0rMono
				BitMask,
				ham3000c02v1EmbG4p1l
				AudioMxInputB,
				ham3000c02v1EmbG4p1lMonPh
				Bit0Nor1Inv,
				ham3000c02v1EmbG4p1lMono
				BitMask,
				ham3000c02v1EmbG4p1r
				AudioMxInputB,
				ham3000c02v1EmbG4p1rMonPh
				Bit0Nor1Inv,
				ham3000c02v1EmbG4p1rMono
				BitMask,
				ham3000c02v1AesOut1L
				AudioMxInputB,
				ham3000c02v1AesOut1lMonPh
				Bit0Nor1Inv,
				ham3000c02v1AesOut1lMono
				BitMask,
				ham3000c02v1AesOut1R
				AudioMxInputB,
				ham3000c02v1AesOut1rMonPh
				Bit0Nor1Inv,
				ham3000c02v1AesOut1rMono
				BitMask,
				ham3000c02v1AesOut2L
				AudioMxInputB,
				ham3000c02v1AesOut2lMonPh
				Bit0Nor1Inv,
				ham3000c02v1AesOut2lMono
				BitMask,
				ham3000c02v1AesOut2R
				AudioMxInputB,
				ham3000c02v1AesOut2rMonPh
				Bit0Nor1Inv,
				ham3000c02v1AesOut2rMono
				BitMask,
				ham3000c02v1GanG1p0l
				Gain24dbMute,
				ham3000c02v1PhaseG1p0l
				Bit0Nor1Inv,
				ham3000c02v1GanG1p0r
				Gain24dbMute,
				ham3000c02v1PhaseG1p0r
				Bit0Nor1Inv,
				ham3000c02v1GanG1p1l
				Gain24dbMute,
				ham3000c02v1PhaseG1p1l
				Bit0Nor1Inv,
				ham3000c02v1GanG1p1r
				Gain24dbMute,
				ham3000c02v1PhaseG1p1r
				Bit0Nor1Inv,
				ham3000c02v1GanG2p0l
				Gain24dbMute,
				ham3000c02v1PhaseG2p0l
				Bit0Nor1Inv,
				ham3000c02v1GanG2p0r
				Gain24dbMute,
				ham3000c02v1PhaseG2p0r
				Bit0Nor1Inv,
				ham3000c02v1GanG2p1l
				Gain24dbMute,
				ham3000c02v1PhaseG2p1l
				Bit0Nor1Inv,
				ham3000c02v1GanG2p1r
				Gain24dbMute,
				ham3000c02v1PhaseG2p1r
				Bit0Nor1Inv,
				ham3000c02v1GanG3p0l
				Gain24dbMute,
				ham3000c02v1PhaseG3p0l
				Bit0Nor1Inv,
				ham3000c02v1GanG3p0r
				Gain24dbMute,
				ham3000c02v1PhaseG3p0r
				Bit0Nor1Inv,
				ham3000c02v1GanG3p1l
				Gain24dbMute,
				ham3000c02v1PhaseG3p1l
				Bit0Nor1Inv,
				ham3000c02v1GanG3p1r
				Gain24dbMute,
				ham3000c02v1PhaseG3p1r
				Bit0Nor1Inv,
				ham3000c02v1GanG4p0l
				Gain24dbMute,
				ham3000c02v1PhaseG4p0l
				Bit0Nor1Inv,
				ham3000c02v1GanG4p0r
				Gain24dbMute,
				ham3000c02v1PhaseG4p0r
				Bit0Nor1Inv,
				ham3000c02v1GanG4p1l
				Gain24dbMute,
				ham3000c02v1PhaseG4p1l
				Bit0Nor1Inv,
				ham3000c02v1GanG4p1r
				Gain24dbMute,
				ham3000c02v1PhaseG4p1r
				Bit0Nor1Inv,
				ham3000c02v1GanAes1l
				Gain24dbMute,
				ham3000c02v1PhaseAes1l
				Bit0Nor1Inv,
				ham3000c02v1GanAes1r
				Gain24dbMute,
				ham3000c02v1PhaseAes1r
				Bit0Nor1Inv,
				ham3000c02v1GanAes2l
				Gain24dbMute,
				ham3000c02v1PhaseAes2l
				Bit0Nor1Inv,
				ham3000c02v1GanAes2r
				Gain24dbMute,
				ham3000c02v1PhaseAes2r
				Bit0Nor1Inv,
				ham3000c02v1DelayG1p0l
				DelayAud,
				ham3000c02v1DelayG1p0r
				DelayAud,
				ham3000c02v1DelayG1p1l
				DelayAud,
				ham3000c02v1DelayG1p1r
				DelayAud,
				ham3000c02v1DelayG2p0l
				DelayAud,
				ham3000c02v1DelayG2p0r
				DelayAud,
				ham3000c02v1DelayG2p1l
				DelayAud,
				ham3000c02v1DelayG2p1r
				DelayAud,
				ham3000c02v1DelayG3p0l
				DelayAud,
				ham3000c02v1DelayG3p0r
				DelayAud,
				ham3000c02v1DelayG3p1l
				DelayAud,
				ham3000c02v1DelayG3p1r
				DelayAud,
				ham3000c02v1DelayG4p0l
				DelayAud,
				ham3000c02v1DelayG4p0r
				DelayAud,
				ham3000c02v1DelayG4p1l
				DelayAud,
				ham3000c02v1DelayG4p1r
				DelayAud,
				ham3000c02v1DelayAes1l
				DelayAud,
				ham3000c02v1DelayAes1r
				DelayAud,
				ham3000c02v1DelayAes2l
				DelayAud,
				ham3000c02v1DelayAes2r
				DelayAud,
				ham3000c02v1StatFlash
				BitFailN,
				ham3000c02v1NoSignalMain
				BitFail,
				ham3000c02v1NoSignalMainTrapEnable
				AlarmEnable,
				ham3000c02v1UnlockMain
				BitFail,
				ham3000c02v1UnlockMainTrapEnable
				AlarmEnable,
				ham3000c02v1EdhErrorMain
				BitFail,
				ham3000c02v1EdhErrorMainTrapEnable
				AlarmEnable,
				ham3000c02v1NoSignalAux
				BitFail,
				ham3000c02v1UnlockAux
				BitFail,
				ham3000c02v1EdhErrorAux
				BitFail,
				ham3000c02v1RefAbsent
				BitFail,
				ham3000c02v1RefAbsentTrapEnable
				AlarmEnable,
				ham3000c02v1RefUnlock
				BitFail,
				ham3000c02v1RefUnlockTrapEnable
				AlarmEnable,
				ham3000c02v1FormatMainIn
				SdiHd3gFmt3,
				ham3000c02v1FormatAuxIn
				SdiHd3gFmt3,
				ham3000c02v1FormatRef
				SdiHd3gFmt3,
				ham3000c02v1FormatMainTx
				SdiHd3gFmt3,
				ham3000c02v1SigDelay
				DelayX20Us,
				ham3000c02v1Gr1MainPres
				Bit0No1Yes,
				ham3000c02v1Gr1MainPresTrapEnable
				AlarmEnable,
				ham3000c02v1Gr2MainPres
				Bit0No1Yes,
				ham3000c02v1Gr2MainPresTrapEnable
				AlarmEnable,
				ham3000c02v1Gr3MainPres
				Bit0No1Yes,
				ham3000c02v1Gr3MainPresTrapEnable
				AlarmEnable,
				ham3000c02v1Gr4MainPres
				Bit0No1Yes,
				ham3000c02v1Gr4MainPresTrapEnable
				AlarmEnable,
				ham3000c02v1Gr1AuxPres
				Bit0No1Yes,
				ham3000c02v1Gr2AuxPres
				Bit0No1Yes,
				ham3000c02v1Gr3AuxPres
				Bit0No1Yes,
				ham3000c02v1Gr4AuxPres
				Bit0No1Yes,
				ham3000c02v1Aes1Ok
				BitFailN,
				ham3000c02v1Aes1Frq
				AudioSelFreq6,
				ham3000c02v1Aes2Ok
				BitFailN,
				ham3000c02v1Aes2Frq
				AudioSelFreq6,
				ham3000c02v1AudStatMain
				BitFail,
				ham3000c02v1AudStatMainTrapEnable
				AlarmEnable,
				ham3000c02v1AudStatAux
				BitFail,
				ham3000c02v1AudStatAuxTrapEnable
				AlarmEnable,
				ham3000c02v1AudStatAes1
				BitFail,
				ham3000c02v1AudStatAes1TrapEnable
				AlarmEnable,
				ham3000c02v1AudStatAes2
				BitFail,
				ham3000c02v1AudStatAes2TrapEnable
				AlarmEnable,
				ham3000c02v1AudStatAnlg1
				BitFail,
				ham3000c02v1AudStatAnlg1TrapEnable
				AlarmEnable,
				ham3000c02v1AudStatAnlg2
				BitFail,
				ham3000c02v1AudStatAnlg2TrapEnable
				AlarmEnable,
				ham3000c02v1OvldPgmOut
				BitFail,
				ham3000c02v1OvldPgmOutTrapEnable
				AlarmEnable,
				ham3000c02v1OvldAes1Out
				BitFail,
				ham3000c02v1OvldAes1OutTrapEnable
				AlarmEnable,
				ham3000c02v1OvldAes2Out
				BitFail,
				ham3000c02v1OvldAes2OutTrapEnable
				AlarmEnable,
				ham3000c02v1SilPgmOut
				BitFail,
				ham3000c02v1SilPgmOutTrapEnable
				AlarmEnable,
				ham3000c02v1SilAes1Out
				BitFail,
				ham3000c02v1SilAes1OutTrapEnable
				AlarmEnable,
				ham3000c02v1SilAes2Out
				BitFail,
				ham3000c02v1SilAes2OutTrapEnable
				AlarmEnable,
				ham3000c02v1SerialNo
				SerialNo,
				ham3000c02v1SavePreset
				Preset16Save,
				ham3000c02v1VidAuxSel
				Bit0Aux1Pgm
			 }

		-- 1.3.6.1.4.1.10106.3.101291.1.1.1
		ham3000c02v1Index OBJECT-TYPE
			SYNTAX ModuleIndex
			MAX-ACCESS read-only
			STATUS current
			DESCRIPTION
				"Index of HAM3000C02V1 Table"
		::= { ham3000c02v1Entry 1 }

		-- 1.3.6.1.4.1.10106.3.101291.1.1.3
		ham3000c02v1ActivePreset OBJECT-TYPE
			SYNTAX Preset16Active
			MAX-ACCESS read-only
			STATUS current
			DESCRIPTION
				"Shows the active preset"
		::= { ham3000c02v1Entry 3 }

		-- 1.3.6.1.4.1.10106.3.101291.1.1.5
		ham3000c02v1LoadPreset OBJECT-TYPE
			SYNTAX Preset16Load
			MAX-ACCESS read-write
			STATUS current
			DESCRIPTION
				"Allows loading a preset"
		::= { ham3000c02v1Entry 5 }

		-- 1.3.6.1.4.1.10106.3.101291.1.1.7
		ham3000c02v1SynchroMode OBJECT-TYPE
			SYNTAX Bit0Fra1Lin
			MAX-ACCESS read-write
			STATUS current
			DESCRIPTION
				"Allows selecting the synchronizing mode"
		::= { ham3000c02v1Entry 7 }

		-- 1.3.6.1.4.1.10106.3.101291.1.1.9
		ham3000c02v1FailMode OBJECT-TYPE
			SYNTAX Bit0Fre1Blk
			MAX-ACCESS read-write
			STATUS current
			DESCRIPTION
				"Allows selecting the output video signal if the input fails"
		::= { ham3000c02v1Entry 9 }

		-- 1.3.6.1.4.1.10106.3.101291.1.1.11
		ham3000c02v1DelayMode OBJECT-TYPE
			SYNTAX Bit0Syn1De2
			MAX-ACCESS read-write
			STATUS current
			DESCRIPTION
				"Allows selecting the operating mode"
		::= { ham3000c02v1Entry 11 }

		-- 1.3.6.1.4.1.10106.3.101291.1.1.13
		ham3000c02v1HDelay OBJECT-TYPE
			SYNTAX DelayPixel5
			MAX-ACCESS read-write
			STATUS current
			DESCRIPTION
				"Allows adjusting the video horizontal delay"
		::= { ham3000c02v1Entry 13 }

		-- 1.3.6.1.4.1.10106.3.101291.1.1.15
		ham3000c02v1FrameDelay OBJECT-TYPE
			SYNTAX DelayFram5
			MAX-ACCESS read-write
			STATUS current
			DESCRIPTION
				"Allows adjusting the frame delay"
		::= { ham3000c02v1Entry 15 }

		-- 1.3.6.1.4.1.10106.3.101291.1.1.17
		ham3000c02v1VDelay OBJECT-TYPE
			SYNTAX DelayLines2
			MAX-ACCESS read-write
			STATUS current
			DESCRIPTION
				"Allows adjusting the video vertical delay"
		::= { ham3000c02v1Entry 17 }

		-- 1.3.6.1.4.1.10106.3.101291.1.1.19
		ham3000c02v1MuxAuxC1 OBJECT-TYPE
			SYNTAX AudioMxInput6
			MAX-ACCESS read-write
			STATUS current
			DESCRIPTION
				"Selects the channel 1 from the input video signal AUX IN"
		::= { ham3000c02v1Entry 19 }

		-- 1.3.6.1.4.1.10106.3.101291.1.1.21
		ham3000c02v1MuxAuxC2 OBJECT-TYPE
			SYNTAX AudioMxInput6
			MAX-ACCESS read-write
			STATUS current
			DESCRIPTION
				"Selects the channel 2 from the input video signal AUX IN"
		::= { ham3000c02v1Entry 21 }

		-- 1.3.6.1.4.1.10106.3.101291.1.1.23
		ham3000c02v1MuxAuxC3 OBJECT-TYPE
			SYNTAX AudioMxInput6
			MAX-ACCESS read-write
			STATUS current
			DESCRIPTION
				"Selects the channel 3 from the input video signal AUX IN"
		::= { ham3000c02v1Entry 23 }

		-- 1.3.6.1.4.1.10106.3.101291.1.1.25
		ham3000c02v1MuxAuxC4 OBJECT-TYPE
			SYNTAX AudioMxInput6
			MAX-ACCESS read-write
			STATUS current
			DESCRIPTION
				"Selects the channel 4 from the input video signal AUX IN"
		::= { ham3000c02v1Entry 25 }

		-- 1.3.6.1.4.1.10106.3.101291.1.1.27
		ham3000c02v1FullScaleLev OBJECT-TYPE
			SYNTAX LevelDbu
			MAX-ACCESS read-write
			STATUS current
			DESCRIPTION
				"Full scale level"
		::= { ham3000c02v1Entry 27 }

		-- 1.3.6.1.4.1.10106.3.101291.1.1.29
		ham3000c02v1OvldLevel OBJECT-TYPE
			SYNTAX LevelDbfs4
			MAX-ACCESS read-write
			STATUS current
			DESCRIPTION
				"Allows adjusting the threshold level for the overload detector"
		::= { ham3000c02v1Entry 29 }

		-- 1.3.6.1.4.1.10106.3.101291.1.1.31
		ham3000c02v1SilenceLevel OBJECT-TYPE
			SYNTAX LevelDbfs3
			MAX-ACCESS read-write
			STATUS current
			DESCRIPTION
				"Allows adjusting the threshold level for the silence detector"
		::= { ham3000c02v1Entry 31 }

		-- 1.3.6.1.4.1.10106.3.101291.1.1.33
		ham3000c02v1SilenceTime OBJECT-TYPE
			SYNTAX TimeS2
			MAX-ACCESS read-write
			STATUS current
			DESCRIPTION
				"Allows adjusting the silence time"
		::= { ham3000c02v1Entry 33 }

		-- 1.3.6.1.4.1.10106.3.101291.1.1.35
		ham3000c02v1Gen1PipsTone OBJECT-TYPE
			SYNTAX Bit0Pips1Wav
			MAX-ACCESS read-write
			STATUS current
			DESCRIPTION
				"Selects the type of signal to be generated at channel 1 of the generator: Greenwich Time Signals (Pips) or a sinewave"
		::= { ham3000c02v1Entry 35 }

		-- 1.3.6.1.4.1.10106.3.101291.1.1.37
		ham3000c02v1Gen2PipsTone OBJECT-TYPE
			SYNTAX Bit0Pips1Wav
			MAX-ACCESS read-write
			STATUS current
			DESCRIPTION
				"Selects the type of signal to be generated at channel 2 of the generator: Greenwich Time Signals (Pips) or a sinewave"
		::= { ham3000c02v1Entry 37 }

		-- 1.3.6.1.4.1.10106.3.101291.1.1.39
		ham3000c02v1MediasGen1 OBJECT-TYPE
			SYNTAX BitMask
			MAX-ACCESS read-write
			STATUS current
			DESCRIPTION
				"Enables the pips sounding at half past at channel 1 of the generator"
		::= { ham3000c02v1Entry 39 }

		-- 1.3.6.1.4.1.10106.3.101291.1.1.41
		ham3000c02v1MediasGen2 OBJECT-TYPE
			SYNTAX BitMask
			MAX-ACCESS read-write
			STATUS current
			DESCRIPTION
				"Enables the pips sounding at half past at channel 2 of the generator"
		::= { ham3000c02v1Entry 41 }

		-- 1.3.6.1.4.1.10106.3.101291.1.1.43
		ham3000c02v1FreqPips1 OBJECT-TYPE
			SYNTAX FrqGen
			MAX-ACCESS read-write
			STATUS current
			DESCRIPTION
				"Frequency of the sound signals generated at channel 1"
		::= { ham3000c02v1Entry 43 }

		-- 1.3.6.1.4.1.10106.3.101291.1.1.45
		ham3000c02v1FreqPips2 OBJECT-TYPE
			SYNTAX FrqGen
			MAX-ACCESS read-write
			STATUS current
			DESCRIPTION
				"Frequency of the sound singals generated at channel 2"
		::= { ham3000c02v1Entry 45 }

		-- 1.3.6.1.4.1.10106.3.101291.1.1.47
		ham3000c02v1LevelPips1 OBJECT-TYPE
			SYNTAX LevelDbfsD
			MAX-ACCESS read-write
			STATUS current
			DESCRIPTION
				"Amplitude of the sound signals generated at channel 1"
		::= { ham3000c02v1Entry 47 }

		-- 1.3.6.1.4.1.10106.3.101291.1.1.49
		ham3000c02v1LevelPips2 OBJECT-TYPE
			SYNTAX LevelDbfsD
			MAX-ACCESS read-write
			STATUS current
			DESCRIPTION
				"Amplitude of the sound signals generated at channel 2"
		::= { ham3000c02v1Entry 49 }

		-- 1.3.6.1.4.1.10106.3.101291.1.1.51
		ham3000c02v1NPipsHour OBJECT-TYPE
			SYNTAX Uint4
			MAX-ACCESS read-write
			STATUS current
			DESCRIPTION
				"Number of short pips generated at o'clock"
		::= { ham3000c02v1Entry 51 }

		-- 1.3.6.1.4.1.10106.3.101291.1.1.53
		ham3000c02v1NPipsHalf OBJECT-TYPE
			SYNTAX Uint4
			MAX-ACCESS read-write
			STATUS current
			DESCRIPTION
				"Number of short pips generated at half past"
		::= { ham3000c02v1Entry 53 }

		-- 1.3.6.1.4.1.10106.3.101291.1.1.55
		ham3000c02v1ShortPerHour OBJECT-TYPE
			SYNTAX TimeX100Ms
			MAX-ACCESS read-write
			STATUS current
			DESCRIPTION
				"Length of o'clock short pips"
		::= { ham3000c02v1Entry 55 }

		-- 1.3.6.1.4.1.10106.3.101291.1.1.57
		ham3000c02v1ShortPerHalf OBJECT-TYPE
			SYNTAX TimeX100Ms
			MAX-ACCESS read-write
			STATUS current
			DESCRIPTION
				"Length of half past short pips"
		::= { ham3000c02v1Entry 57 }

		-- 1.3.6.1.4.1.10106.3.101291.1.1.59
		ham3000c02v1LongPerHour OBJECT-TYPE
			SYNTAX TimeX100Ms
			MAX-ACCESS read-write
			STATUS current
			DESCRIPTION
				"Length of o'clock long pip"
		::= { ham3000c02v1Entry 59 }

		-- 1.3.6.1.4.1.10106.3.101291.1.1.61
		ham3000c02v1LongPerHalf OBJECT-TYPE
			SYNTAX TimeX100Ms
			MAX-ACCESS read-write
			STATUS current
			DESCRIPTION
				"Length of half past long pip"
		::= { ham3000c02v1Entry 61 }

		-- 1.3.6.1.4.1.10106.3.101291.1.1.63
		ham3000c02v1EmbG1p0l OBJECT-TYPE
			SYNTAX AudioMxInputB
			MAX-ACCESS read-write
			STATUS current
			DESCRIPTION
				"Audio channel assignment to the audio channel embedded in G1P0L PGM OUT"
		::= { ham3000c02v1Entry 63 }

		-- 1.3.6.1.4.1.10106.3.101291.1.1.65
		ham3000c02v1EmbG1p0lMonPh OBJECT-TYPE
			SYNTAX Bit0Nor1Inv
			MAX-ACCESS read-write
			STATUS current
			DESCRIPTION
				"Phase applied to the secundary channel in the stereophonic audio pair for generating the monophonic audio in G1P0L PGM OUT"
		::= { ham3000c02v1Entry 65 }

		-- 1.3.6.1.4.1.10106.3.101291.1.1.67
		ham3000c02v1EmbG1p0lMono OBJECT-TYPE
			SYNTAX BitMask
			MAX-ACCESS read-write
			STATUS current
			DESCRIPTION
				"Monophonic audio generated from the audio pair assigned to G1P0L PGM OUT"
		::= { ham3000c02v1Entry 67 }

		-- 1.3.6.1.4.1.10106.3.101291.1.1.69
		ham3000c02v1EmbG1p0r OBJECT-TYPE
			SYNTAX AudioMxInputB
			MAX-ACCESS read-write
			STATUS current
			DESCRIPTION
				"Audio channel assignment to the audio channel embedded in G1P0R PGM OUT"
		::= { ham3000c02v1Entry 69 }

		-- 1.3.6.1.4.1.10106.3.101291.1.1.71
		ham3000c02v1EmbG1p0rMonPh OBJECT-TYPE
			SYNTAX Bit0Nor1Inv
			MAX-ACCESS read-write
			STATUS current
			DESCRIPTION
				"Phase applied to the secundary channel in the stereophonic audio pair for generating the monophonic audio in G1P0R PGM OUT"
		::= { ham3000c02v1Entry 71 }

		-- 1.3.6.1.4.1.10106.3.101291.1.1.73
		ham3000c02v1EmbG1p0rMono OBJECT-TYPE
			SYNTAX BitMask
			MAX-ACCESS read-write
			STATUS current
			DESCRIPTION
				"Monophonic audio generated from the audio pair assigned to G1P0R PGM OUT"
		::= { ham3000c02v1Entry 73 }

		-- 1.3.6.1.4.1.10106.3.101291.1.1.75
		ham3000c02v1EmbG1p1l OBJECT-TYPE
			SYNTAX AudioMxInputB
			MAX-ACCESS read-write
			STATUS current
			DESCRIPTION
				"Audio channel assignment to the audio channel embedded in G1P1L PGM OUT"
		::= { ham3000c02v1Entry 75 }

		-- 1.3.6.1.4.1.10106.3.101291.1.1.77
		ham3000c02v1EmbG1p1lMonPh OBJECT-TYPE
			SYNTAX Bit0Nor1Inv
			MAX-ACCESS read-write
			STATUS current
			DESCRIPTION
				"Phase applied to the secundary channel in the stereophonic audio pair for generating the monophonic audio in G1P1L PGM OUT"
		::= { ham3000c02v1Entry 77 }

		-- 1.3.6.1.4.1.10106.3.101291.1.1.79
		ham3000c02v1EmbG1p1lMono OBJECT-TYPE
			SYNTAX BitMask
			MAX-ACCESS read-write
			STATUS current
			DESCRIPTION
				"Monophonic audio generated from the audio pair assigned to G1P1L PGM OUT"
		::= { ham3000c02v1Entry 79 }

		-- 1.3.6.1.4.1.10106.3.101291.1.1.81
		ham3000c02v1EmbG1p1r OBJECT-TYPE
			SYNTAX AudioMxInputB
			MAX-ACCESS read-write
			STATUS current
			DESCRIPTION
				"Audio channel assignment to the audio channel embedded in G1P1R PGM OUT"
		::= { ham3000c02v1Entry 81 }

		-- 1.3.6.1.4.1.10106.3.101291.1.1.83
		ham3000c02v1EmbG1p1rMonPh OBJECT-TYPE
			SYNTAX Bit0Nor1Inv
			MAX-ACCESS read-write
			STATUS current
			DESCRIPTION
				"Phase applied to the secundary channel in the stereophonic audio pair for generating the monophonic audio in G1P1R PGM OUT"
		::= { ham3000c02v1Entry 83 }

		-- 1.3.6.1.4.1.10106.3.101291.1.1.85
		ham3000c02v1EmbG1p1rMono OBJECT-TYPE
			SYNTAX BitMask
			MAX-ACCESS read-write
			STATUS current
			DESCRIPTION
				"Monophonic audio generated from the audio pair assigned to G1P1R PGM OUT"
		::= { ham3000c02v1Entry 85 }

		-- 1.3.6.1.4.1.10106.3.101291.1.1.87
		ham3000c02v1EmbG2p0l OBJECT-TYPE
			SYNTAX AudioMxInputB
			MAX-ACCESS read-write
			STATUS current
			DESCRIPTION
				"Audio channel assignment to the audio channel embedded in G2P0L PGM OUT"
		::= { ham3000c02v1Entry 87 }

		-- 1.3.6.1.4.1.10106.3.101291.1.1.89
		ham3000c02v1EmbG2p0lMonPh OBJECT-TYPE
			SYNTAX Bit0Nor1Inv
			MAX-ACCESS read-write
			STATUS current
			DESCRIPTION
				"Phase applied to the secundary channel in the stereophonic audio pair for generating the monophonic audio in G2P0L PGM OUT"
		::= { ham3000c02v1Entry 89 }

		-- 1.3.6.1.4.1.10106.3.101291.1.1.91
		ham3000c02v1EmbG2p0lMono OBJECT-TYPE
			SYNTAX BitMask
			MAX-ACCESS read-write
			STATUS current
			DESCRIPTION
				"Monophonic audio generated from the audio pair assigned to G2P0L PGM OUT"
		::= { ham3000c02v1Entry 91 }

		-- 1.3.6.1.4.1.10106.3.101291.1.1.93
		ham3000c02v1EmbG2p0r OBJECT-TYPE
			SYNTAX AudioMxInputB
			MAX-ACCESS read-write
			STATUS current
			DESCRIPTION
				"Audio channel assignment to the audio channel embedded in G2P0R PGM OUT"
		::= { ham3000c02v1Entry 93 }

		-- 1.3.6.1.4.1.10106.3.101291.1.1.95
		ham3000c02v1EmbG2p0rMonPh OBJECT-TYPE
			SYNTAX Bit0Nor1Inv
			MAX-ACCESS read-write
			STATUS current
			DESCRIPTION
				"Phase applied to the secundary channel in the stereophonic audio pair for generating the monophonic audio in G2P0R PGM OUT"
		::= { ham3000c02v1Entry 95 }

		-- 1.3.6.1.4.1.10106.3.101291.1.1.97
		ham3000c02v1EmbG2p0rMono OBJECT-TYPE
			SYNTAX BitMask
			MAX-ACCESS read-write
			STATUS current
			DESCRIPTION
				"Monophonic audio generated from the audio pair assigned to G2P0R PGM OUT"
		::= { ham3000c02v1Entry 97 }

		-- 1.3.6.1.4.1.10106.3.101291.1.1.99
		ham3000c02v1EmbG2p1l OBJECT-TYPE
			SYNTAX AudioMxInputB
			MAX-ACCESS read-write
			STATUS current
			DESCRIPTION
				"Audio channel assignment to the audio channel embedded in G2P1L PGM OUT"
		::= { ham3000c02v1Entry 99 }

		-- 1.3.6.1.4.1.10106.3.101291.1.1.101
		ham3000c02v1EmbG2p1lMonPh OBJECT-TYPE
			SYNTAX Bit0Nor1Inv
			MAX-ACCESS read-write
			STATUS current
			DESCRIPTION
				"Phase applied to the secundary channel in the stereophonic audio pair for generating the monophonic audio in G2P1L PGM OUT"
		::= { ham3000c02v1Entry 101 }

		-- 1.3.6.1.4.1.10106.3.101291.1.1.103
		ham3000c02v1EmbG2p1lMono OBJECT-TYPE
			SYNTAX BitMask
			MAX-ACCESS read-write
			STATUS current
			DESCRIPTION
				"Monophonic audio generated from the audio pair assigned to G2P1L PGM OUT"
		::= { ham3000c02v1Entry 103 }

		-- 1.3.6.1.4.1.10106.3.101291.1.1.105
		ham3000c02v1EmbG2p1r OBJECT-TYPE
			SYNTAX AudioMxInputB
			MAX-ACCESS read-write
			STATUS current
			DESCRIPTION
				"Audio channel assignment to the audio channel embedded in G2P1R PGM OUT"
		::= { ham3000c02v1Entry 105 }

		-- 1.3.6.1.4.1.10106.3.101291.1.1.107
		ham3000c02v1EmbG2p1rMonPh OBJECT-TYPE
			SYNTAX Bit0Nor1Inv
			MAX-ACCESS read-write
			STATUS current
			DESCRIPTION
				"Phase applied to the secundary channel in the stereophonic audio pair for generating the monophonic audio in G2P1R PGM OUT"
		::= { ham3000c02v1Entry 107 }

		-- 1.3.6.1.4.1.10106.3.101291.1.1.109
		ham3000c02v1EmbG2p1rMono OBJECT-TYPE
			SYNTAX BitMask
			MAX-ACCESS read-write
			STATUS current
			DESCRIPTION
				"Monophonic audio generated from the audio pair assigned to G2P1R PGM OUT"
		::= { ham3000c02v1Entry 109 }

		-- 1.3.6.1.4.1.10106.3.101291.1.1.111
		ham3000c02v1EmbG3p0l OBJECT-TYPE
			SYNTAX AudioMxInputB
			MAX-ACCESS read-write
			STATUS current
			DESCRIPTION
				"Audio channel assignment to the audio channel embedded in G3P0L PGM OUT"
		::= { ham3000c02v1Entry 111 }

		-- 1.3.6.1.4.1.10106.3.101291.1.1.113
		ham3000c02v1EmbG3p0lMonPh OBJECT-TYPE
			SYNTAX Bit0Nor1Inv
			MAX-ACCESS read-write
			STATUS current
			DESCRIPTION
				"Phase applied to the secundary channel in the stereophonic audio pair for generating the monophonic audio in G3P0L PGM OUT"
		::= { ham3000c02v1Entry 113 }

		-- 1.3.6.1.4.1.10106.3.101291.1.1.115
		ham3000c02v1EmbG3p0lMono OBJECT-TYPE
			SYNTAX BitMask
			MAX-ACCESS read-write
			STATUS current
			DESCRIPTION
				"Monophonic audio generated from the audio pair assigned to G3P0L PGM OUT"
		::= { ham3000c02v1Entry 115 }

		-- 1.3.6.1.4.1.10106.3.101291.1.1.117
		ham3000c02v1EmbG3p0r OBJECT-TYPE
			SYNTAX AudioMxInputB
			MAX-ACCESS read-write
			STATUS current
			DESCRIPTION
				"Audio channel assignment to the audio channel embedded in G3P0R PGM OUT"
		::= { ham3000c02v1Entry 117 }

		-- 1.3.6.1.4.1.10106.3.101291.1.1.119
		ham3000c02v1EmbG3p0rMonPh OBJECT-TYPE
			SYNTAX Bit0Nor1Inv
			MAX-ACCESS read-write
			STATUS current
			DESCRIPTION
				"Phase applied to the secundary channel in the stereophonic audio pair for generating the monophonic audio in G3P0R PGM OUT"
		::= { ham3000c02v1Entry 119 }

		-- 1.3.6.1.4.1.10106.3.101291.1.1.121
		ham3000c02v1EmbG3p0rMono OBJECT-TYPE
			SYNTAX BitMask
			MAX-ACCESS read-write
			STATUS current
			DESCRIPTION
				"Monophonic audio generated from the audio pair assigned to G3P0R PGM OUT"
		::= { ham3000c02v1Entry 121 }

		-- 1.3.6.1.4.1.10106.3.101291.1.1.123
		ham3000c02v1EmbG3p1l OBJECT-TYPE
			SYNTAX AudioMxInputB
			MAX-ACCESS read-write
			STATUS current
			DESCRIPTION
				"Audio channel assignment to the audio channel embedded in G3P1L PGM OUT"
		::= { ham3000c02v1Entry 123 }

		-- 1.3.6.1.4.1.10106.3.101291.1.1.125
		ham3000c02v1EmbG3p1lMonPh OBJECT-TYPE
			SYNTAX Bit0Nor1Inv
			MAX-ACCESS read-write
			STATUS current
			DESCRIPTION
				"Phase applied to the secundary channel in the stereophonic audio pair for generating the monophonic audio in G3P1L PGM OUT"
		::= { ham3000c02v1Entry 125 }

		-- 1.3.6.1.4.1.10106.3.101291.1.1.127
		ham3000c02v1EmbG3p1lMono OBJECT-TYPE
			SYNTAX BitMask
			MAX-ACCESS read-write
			STATUS current
			DESCRIPTION
				"Monophonic audio generated from the audio pair assigned to G3P1L PGM OUT"
		::= { ham3000c02v1Entry 127 }

		-- 1.3.6.1.4.1.10106.3.101291.1.1.129
		ham3000c02v1EmbG3p1r OBJECT-TYPE
			SYNTAX AudioMxInputB
			MAX-ACCESS read-write
			STATUS current
			DESCRIPTION
				"Audio channel assignment to the audio channel embedded in G3P1R PGM OUT"
		::= { ham3000c02v1Entry 129 }

		-- 1.3.6.1.4.1.10106.3.101291.1.1.131
		ham3000c02v1EmbG3p1rMonPh OBJECT-TYPE
			SYNTAX Bit0Nor1Inv
			MAX-ACCESS read-write
			STATUS current
			DESCRIPTION
				"Phase applied to the secundary channel in the stereophonic audio pair for generating the monophonic audio in G3P1R PGM OUT"
		::= { ham3000c02v1Entry 131 }

		-- 1.3.6.1.4.1.10106.3.101291.1.1.133
		ham3000c02v1EmbG3p1rMono OBJECT-TYPE
			SYNTAX BitMask
			MAX-ACCESS read-write
			STATUS current
			DESCRIPTION
				"Monophonic audio generated from the audio pair assigned to G3P1R PGM OUT"
		::= { ham3000c02v1Entry 133 }

		-- 1.3.6.1.4.1.10106.3.101291.1.1.135
		ham3000c02v1EmbG4p0l OBJECT-TYPE
			SYNTAX AudioMxInputB
			MAX-ACCESS read-write
			STATUS current
			DESCRIPTION
				"Audio channel assignment to the audio channel embedded in G4P0L PGM OUT"
		::= { ham3000c02v1Entry 135 }

		-- 1.3.6.1.4.1.10106.3.101291.1.1.137
		ham3000c02v1EmbG4p0lMonPh OBJECT-TYPE
			SYNTAX Bit0Nor1Inv
			MAX-ACCESS read-write
			STATUS current
			DESCRIPTION
				"Phase applied to the secundary channel in the stereophonic audio pair for generating the monophonic audio in G4P0L PGM OUT"
		::= { ham3000c02v1Entry 137 }

		-- 1.3.6.1.4.1.10106.3.101291.1.1.139
		ham3000c02v1EmbG4p0lMono OBJECT-TYPE
			SYNTAX BitMask
			MAX-ACCESS read-write
			STATUS current
			DESCRIPTION
				"Monophonic audio generated from the audio pair assigned to G4P0L PGM OUT"
		::= { ham3000c02v1Entry 139 }

		-- 1.3.6.1.4.1.10106.3.101291.1.1.141
		ham3000c02v1EmbG4p0r OBJECT-TYPE
			SYNTAX AudioMxInputB
			MAX-ACCESS read-write
			STATUS current
			DESCRIPTION
				"Audio channel assignment to the audio channel embedded in G4P0R PGM OUT"
		::= { ham3000c02v1Entry 141 }

		-- 1.3.6.1.4.1.10106.3.101291.1.1.143
		ham3000c02v1EmbG4p0rMonPh OBJECT-TYPE
			SYNTAX Bit0Nor1Inv
			MAX-ACCESS read-write
			STATUS current
			DESCRIPTION
				"Phase applied to the secundary channel in the stereophonic audio pair for generating the monophonic audio in G4P0R PGM OUT"
		::= { ham3000c02v1Entry 143 }

		-- 1.3.6.1.4.1.10106.3.101291.1.1.145
		ham3000c02v1EmbG4p0rMono OBJECT-TYPE
			SYNTAX BitMask
			MAX-ACCESS read-write
			STATUS current
			DESCRIPTION
				"Monophonic audio generated from the audio pair assigned to G4P0R PGM OUT"
		::= { ham3000c02v1Entry 145 }

		-- 1.3.6.1.4.1.10106.3.101291.1.1.147
		ham3000c02v1EmbG4p1l OBJECT-TYPE
			SYNTAX AudioMxInputB
			MAX-ACCESS read-write
			STATUS current
			DESCRIPTION
				"Audio channel assignment to the audio channel embedded in G4P1L PGM OUT"
		::= { ham3000c02v1Entry 147 }

		-- 1.3.6.1.4.1.10106.3.101291.1.1.149
		ham3000c02v1EmbG4p1lMonPh OBJECT-TYPE
			SYNTAX Bit0Nor1Inv
			MAX-ACCESS read-write
			STATUS current
			DESCRIPTION
				"Phase applied to the secundary channel in the stereophonic audio pair for generating the monophonic audio in G4P1L PGM OUT"
		::= { ham3000c02v1Entry 149 }

		-- 1.3.6.1.4.1.10106.3.101291.1.1.151
		ham3000c02v1EmbG4p1lMono OBJECT-TYPE
			SYNTAX BitMask
			MAX-ACCESS read-write
			STATUS current
			DESCRIPTION
				"Monophonic audio generated from the audio pair assigned to G4P1L PGM OUT"
		::= { ham3000c02v1Entry 151 }

		-- 1.3.6.1.4.1.10106.3.101291.1.1.153
		ham3000c02v1EmbG4p1r OBJECT-TYPE
			SYNTAX AudioMxInputB
			MAX-ACCESS read-write
			STATUS current
			DESCRIPTION
				"Audio channel assignment to the audio channel embedded in G4P1R PGM OUT"
		::= { ham3000c02v1Entry 153 }

		-- 1.3.6.1.4.1.10106.3.101291.1.1.155
		ham3000c02v1EmbG4p1rMonPh OBJECT-TYPE
			SYNTAX Bit0Nor1Inv
			MAX-ACCESS read-write
			STATUS current
			DESCRIPTION
				"Phase applied to the secundary channel in the stereophonic audio pair for generating the monophonic audio in G4P1R PGM OUT"
		::= { ham3000c02v1Entry 155 }

		-- 1.3.6.1.4.1.10106.3.101291.1.1.157
		ham3000c02v1EmbG4p1rMono OBJECT-TYPE
			SYNTAX BitMask
			MAX-ACCESS read-write
			STATUS current
			DESCRIPTION
				"Monophonic audio generated from the audio pair assigned to G4P1R PGM OUT"
		::= { ham3000c02v1Entry 157 }

		-- 1.3.6.1.4.1.10106.3.101291.1.1.159
		ham3000c02v1AesOut1L OBJECT-TYPE
			SYNTAX AudioMxInputB
			MAX-ACCESS read-write
			STATUS current
			DESCRIPTION
				"Audio channel assignment to the digital audio output AES1L OUT"
		::= { ham3000c02v1Entry 159 }

		-- 1.3.6.1.4.1.10106.3.101291.1.1.161
		ham3000c02v1AesOut1lMonPh OBJECT-TYPE
			SYNTAX Bit0Nor1Inv
			MAX-ACCESS read-write
			STATUS current
			DESCRIPTION
				"Phase applied to the secundary channel in the stereophonic audio pair for generating the monophonic audio in AES1L OUT"
		::= { ham3000c02v1Entry 161 }

		-- 1.3.6.1.4.1.10106.3.101291.1.1.163
		ham3000c02v1AesOut1lMono OBJECT-TYPE
			SYNTAX BitMask
			MAX-ACCESS read-write
			STATUS current
			DESCRIPTION
				"Monophonic audio generated from the audio pair assigned to AES1L OUT"
		::= { ham3000c02v1Entry 163 }

		-- 1.3.6.1.4.1.10106.3.101291.1.1.165
		ham3000c02v1AesOut1R OBJECT-TYPE
			SYNTAX AudioMxInputB
			MAX-ACCESS read-write
			STATUS current
			DESCRIPTION
				"Audio channel assignment to the digital audio output AES1R OUT"
		::= { ham3000c02v1Entry 165 }

		-- 1.3.6.1.4.1.10106.3.101291.1.1.167
		ham3000c02v1AesOut1rMonPh OBJECT-TYPE
			SYNTAX Bit0Nor1Inv
			MAX-ACCESS read-write
			STATUS current
			DESCRIPTION
				"Phase applied to the secundary channel in the stereophonic audio pair for generating the monophonic audio in AES1R OUT"
		::= { ham3000c02v1Entry 167 }

		-- 1.3.6.1.4.1.10106.3.101291.1.1.169
		ham3000c02v1AesOut1rMono OBJECT-TYPE
			SYNTAX BitMask
			MAX-ACCESS read-write
			STATUS current
			DESCRIPTION
				"Monophonic audio generated from the audio pair assigned to AES1R OUT"
		::= { ham3000c02v1Entry 169 }

		-- 1.3.6.1.4.1.10106.3.101291.1.1.171
		ham3000c02v1AesOut2L OBJECT-TYPE
			SYNTAX AudioMxInputB
			MAX-ACCESS read-write
			STATUS current
			DESCRIPTION
				"Audio channel assignment to the digital audio output AES2L OUT"
		::= { ham3000c02v1Entry 171 }

		-- 1.3.6.1.4.1.10106.3.101291.1.1.173
		ham3000c02v1AesOut2lMonPh OBJECT-TYPE
			SYNTAX Bit0Nor1Inv
			MAX-ACCESS read-write
			STATUS current
			DESCRIPTION
				"Phase applied to the secundary channel in the stereophonic audio pair for generating the monophonic audio in AES2L OUT"
		::= { ham3000c02v1Entry 173 }

		-- 1.3.6.1.4.1.10106.3.101291.1.1.175
		ham3000c02v1AesOut2lMono OBJECT-TYPE
			SYNTAX BitMask
			MAX-ACCESS read-write
			STATUS current
			DESCRIPTION
				"Monophonic audio generated from the audio pair assigned to AES2L OUT"
		::= { ham3000c02v1Entry 175 }

		-- 1.3.6.1.4.1.10106.3.101291.1.1.177
		ham3000c02v1AesOut2R OBJECT-TYPE
			SYNTAX AudioMxInputB
			MAX-ACCESS read-write
			STATUS current
			DESCRIPTION
				"Audio channel assignment to the digital audio output AES2R OUT"
		::= { ham3000c02v1Entry 177 }

		-- 1.3.6.1.4.1.10106.3.101291.1.1.179
		ham3000c02v1AesOut2rMonPh OBJECT-TYPE
			SYNTAX Bit0Nor1Inv
			MAX-ACCESS read-write
			STATUS current
			DESCRIPTION
				"Phase applied to the secundary channel in the stereophonic audio pair for generating the monophonic audio in AES2R OUT"
		::= { ham3000c02v1Entry 179 }

		-- 1.3.6.1.4.1.10106.3.101291.1.1.181
		ham3000c02v1AesOut2rMono OBJECT-TYPE
			SYNTAX BitMask
			MAX-ACCESS read-write
			STATUS current
			DESCRIPTION
				"Monophonic audio generated from the audio pair assigned to AES2R OUT"
		::= { ham3000c02v1Entry 181 }

		-- 1.3.6.1.4.1.10106.3.101291.1.1.183
		ham3000c02v1GanG1p0l OBJECT-TYPE
			SYNTAX Gain24dbMute
			MAX-ACCESS read-write
			STATUS current
			DESCRIPTION
				"Gain applied to the digital audio channel embedded in G1P0L PGM OUT"
		::= { ham3000c02v1Entry 183 }

		-- 1.3.6.1.4.1.10106.3.101291.1.1.185
		ham3000c02v1PhaseG1p0l OBJECT-TYPE
			SYNTAX Bit0Nor1Inv
			MAX-ACCESS read-write
			STATUS current
			DESCRIPTION
				"Phase gain applied to the digital audio channel embedded in G1P0L PGM OUT"
		::= { ham3000c02v1Entry 185 }

		-- 1.3.6.1.4.1.10106.3.101291.1.1.187
		ham3000c02v1GanG1p0r OBJECT-TYPE
			SYNTAX Gain24dbMute
			MAX-ACCESS read-write
			STATUS current
			DESCRIPTION
				"Gain applied to the digital audio channel embedded in G1P0R PGM OUT"
		::= { ham3000c02v1Entry 187 }

		-- 1.3.6.1.4.1.10106.3.101291.1.1.189
		ham3000c02v1PhaseG1p0r OBJECT-TYPE
			SYNTAX Bit0Nor1Inv
			MAX-ACCESS read-write
			STATUS current
			DESCRIPTION
				"Phase gain applied to the digital audio channel embedded in G1P0R PGM OUT"
		::= { ham3000c02v1Entry 189 }

		-- 1.3.6.1.4.1.10106.3.101291.1.1.191
		ham3000c02v1GanG1p1l OBJECT-TYPE
			SYNTAX Gain24dbMute
			MAX-ACCESS read-write
			STATUS current
			DESCRIPTION
				"Gain applied to the digital audio channel embedded in G1P1L PGM OUT"
		::= { ham3000c02v1Entry 191 }

		-- 1.3.6.1.4.1.10106.3.101291.1.1.193
		ham3000c02v1PhaseG1p1l OBJECT-TYPE
			SYNTAX Bit0Nor1Inv
			MAX-ACCESS read-write
			STATUS current
			DESCRIPTION
				"Phase gain applied to the digital audio channel embedded in G1P1L PGM OUT"
		::= { ham3000c02v1Entry 193 }

		-- 1.3.6.1.4.1.10106.3.101291.1.1.195
		ham3000c02v1GanG1p1r OBJECT-TYPE
			SYNTAX Gain24dbMute
			MAX-ACCESS read-write
			STATUS current
			DESCRIPTION
				"Gain applied to the digital audio channel embedded in G1P1R PGM OUT"
		::= { ham3000c02v1Entry 195 }

		-- 1.3.6.1.4.1.10106.3.101291.1.1.197
		ham3000c02v1PhaseG1p1r OBJECT-TYPE
			SYNTAX Bit0Nor1Inv
			MAX-ACCESS read-write
			STATUS current
			DESCRIPTION
				"Phase gain applied to the digital audio channel embedded in G1P1R PGM OUT"
		::= { ham3000c02v1Entry 197 }

		-- 1.3.6.1.4.1.10106.3.101291.1.1.199
		ham3000c02v1GanG2p0l OBJECT-TYPE
			SYNTAX Gain24dbMute
			MAX-ACCESS read-write
			STATUS current
			DESCRIPTION
				"Gain applied to the digital audio channel embedded in G2P0L PGM OUT"
		::= { ham3000c02v1Entry 199 }

		-- 1.3.6.1.4.1.10106.3.101291.1.1.201
		ham3000c02v1PhaseG2p0l OBJECT-TYPE
			SYNTAX Bit0Nor1Inv
			MAX-ACCESS read-write
			STATUS current
			DESCRIPTION
				"Phase gain applied to the digital audio channel embedded in G2P0L PGM OUT"
		::= { ham3000c02v1Entry 201 }

		-- 1.3.6.1.4.1.10106.3.101291.1.1.203
		ham3000c02v1GanG2p0r OBJECT-TYPE
			SYNTAX Gain24dbMute
			MAX-ACCESS read-write
			STATUS current
			DESCRIPTION
				"Gain applied to the digital audio channel embedded in G2P0R PGM OUT"
		::= { ham3000c02v1Entry 203 }

		-- 1.3.6.1.4.1.10106.3.101291.1.1.205
		ham3000c02v1PhaseG2p0r OBJECT-TYPE
			SYNTAX Bit0Nor1Inv
			MAX-ACCESS read-write
			STATUS current
			DESCRIPTION
				"Phase gain applied to the digital audio channel embedded in G2P0R PGM OUT"
		::= { ham3000c02v1Entry 205 }

		-- 1.3.6.1.4.1.10106.3.101291.1.1.207
		ham3000c02v1GanG2p1l OBJECT-TYPE
			SYNTAX Gain24dbMute
			MAX-ACCESS read-write
			STATUS current
			DESCRIPTION
				"Gain applied to the digital audio channel embedded in G2P1L PGM OUT"
		::= { ham3000c02v1Entry 207 }

		-- 1.3.6.1.4.1.10106.3.101291.1.1.209
		ham3000c02v1PhaseG2p1l OBJECT-TYPE
			SYNTAX Bit0Nor1Inv
			MAX-ACCESS read-write
			STATUS current
			DESCRIPTION
				"Phase gain applied to the digital audio channel embedded in G2P1L PGM OUT"
		::= { ham3000c02v1Entry 209 }

		-- 1.3.6.1.4.1.10106.3.101291.1.1.211
		ham3000c02v1GanG2p1r OBJECT-TYPE
			SYNTAX Gain24dbMute
			MAX-ACCESS read-write
			STATUS current
			DESCRIPTION
				"Gain applied to the digital audio channel embedded in G2P1R PGM OUT"
		::= { ham3000c02v1Entry 211 }

		-- 1.3.6.1.4.1.10106.3.101291.1.1.213
		ham3000c02v1PhaseG2p1r OBJECT-TYPE
			SYNTAX Bit0Nor1Inv
			MAX-ACCESS read-write
			STATUS current
			DESCRIPTION
				"Phase gain applied to the digital audio channel embedded in G2P1R PGM OUT"
		::= { ham3000c02v1Entry 213 }

		-- 1.3.6.1.4.1.10106.3.101291.1.1.215
		ham3000c02v1GanG3p0l OBJECT-TYPE
			SYNTAX Gain24dbMute
			MAX-ACCESS read-write
			STATUS current
			DESCRIPTION
				"Gain applied to the digital audio channel embedded in G3P0L PGM OUT"
		::= { ham3000c02v1Entry 215 }

		-- 1.3.6.1.4.1.10106.3.101291.1.1.217
		ham3000c02v1PhaseG3p0l OBJECT-TYPE
			SYNTAX Bit0Nor1Inv
			MAX-ACCESS read-write
			STATUS current
			DESCRIPTION
				"Phase gain applied to the digital audio channel embedded in G3P0L PGM OUT"
		::= { ham3000c02v1Entry 217 }

		-- 1.3.6.1.4.1.10106.3.101291.1.1.219
		ham3000c02v1GanG3p0r OBJECT-TYPE
			SYNTAX Gain24dbMute
			MAX-ACCESS read-write
			STATUS current
			DESCRIPTION
				"Gain applied to the digital audio channel embedded in G3P0R PGM OUT"
		::= { ham3000c02v1Entry 219 }

		-- 1.3.6.1.4.1.10106.3.101291.1.1.221
		ham3000c02v1PhaseG3p0r OBJECT-TYPE
			SYNTAX Bit0Nor1Inv
			MAX-ACCESS read-write
			STATUS current
			DESCRIPTION
				"Phase gain applied to the digital audio channel embedded in G3P0R PGM OUT"
		::= { ham3000c02v1Entry 221 }

		-- 1.3.6.1.4.1.10106.3.101291.1.1.223
		ham3000c02v1GanG3p1l OBJECT-TYPE
			SYNTAX Gain24dbMute
			MAX-ACCESS read-write
			STATUS current
			DESCRIPTION
				"Gain applied to the digital audio channel embedded in G3P1L PGM OUT"
		::= { ham3000c02v1Entry 223 }

		-- 1.3.6.1.4.1.10106.3.101291.1.1.225
		ham3000c02v1PhaseG3p1l OBJECT-TYPE
			SYNTAX Bit0Nor1Inv
			MAX-ACCESS read-write
			STATUS current
			DESCRIPTION
				"Phase gain applied to the digital audio channel embedded in G3P1L PGM OUT"
		::= { ham3000c02v1Entry 225 }

		-- 1.3.6.1.4.1.10106.3.101291.1.1.227
		ham3000c02v1GanG3p1r OBJECT-TYPE
			SYNTAX Gain24dbMute
			MAX-ACCESS read-write
			STATUS current
			DESCRIPTION
				"Gain applied to the digital audio channel embedded in G3P1R PGM OUT"
		::= { ham3000c02v1Entry 227 }

		-- 1.3.6.1.4.1.10106.3.101291.1.1.229
		ham3000c02v1PhaseG3p1r OBJECT-TYPE
			SYNTAX Bit0Nor1Inv
			MAX-ACCESS read-write
			STATUS current
			DESCRIPTION
				"Phase gain applied to the digital audio channel embedded in G3P1R PGM OUT"
		::= { ham3000c02v1Entry 229 }

		-- 1.3.6.1.4.1.10106.3.101291.1.1.231
		ham3000c02v1GanG4p0l OBJECT-TYPE
			SYNTAX Gain24dbMute
			MAX-ACCESS read-write
			STATUS current
			DESCRIPTION
				"Gain applied to the digital audio channel embedded in G4P0L PGM OUT"
		::= { ham3000c02v1Entry 231 }

		-- 1.3.6.1.4.1.10106.3.101291.1.1.233
		ham3000c02v1PhaseG4p0l OBJECT-TYPE
			SYNTAX Bit0Nor1Inv
			MAX-ACCESS read-write
			STATUS current
			DESCRIPTION
				"Phase gain applied to the digital audio channel embedded in G4P0L PGM OUT"
		::= { ham3000c02v1Entry 233 }

		-- 1.3.6.1.4.1.10106.3.101291.1.1.235
		ham3000c02v1GanG4p0r OBJECT-TYPE
			SYNTAX Gain24dbMute
			MAX-ACCESS read-write
			STATUS current
			DESCRIPTION
				"Gain applied to the digital audio channel embedded in G4P0R PGM OUT"
		::= { ham3000c02v1Entry 235 }

		-- 1.3.6.1.4.1.10106.3.101291.1.1.237
		ham3000c02v1PhaseG4p0r OBJECT-TYPE
			SYNTAX Bit0Nor1Inv
			MAX-ACCESS read-write
			STATUS current
			DESCRIPTION
				"Phase gain applied to the digital audio channel embedded in G4P0R PGM OUT"
		::= { ham3000c02v1Entry 237 }

		-- 1.3.6.1.4.1.10106.3.101291.1.1.239
		ham3000c02v1GanG4p1l OBJECT-TYPE
			SYNTAX Gain24dbMute
			MAX-ACCESS read-write
			STATUS current
			DESCRIPTION
				"Gain applied to the digital audio channel embedded in G4P1L PGM OUT"
		::= { ham3000c02v1Entry 239 }

		-- 1.3.6.1.4.1.10106.3.101291.1.1.241
		ham3000c02v1PhaseG4p1l OBJECT-TYPE
			SYNTAX Bit0Nor1Inv
			MAX-ACCESS read-write
			STATUS current
			DESCRIPTION
				"Phase gain applied to the digital audio channel embedded in G4P1L PGM OUT"
		::= { ham3000c02v1Entry 241 }

		-- 1.3.6.1.4.1.10106.3.101291.1.1.243
		ham3000c02v1GanG4p1r OBJECT-TYPE
			SYNTAX Gain24dbMute
			MAX-ACCESS read-write
			STATUS current
			DESCRIPTION
				"Gain applied to the digital audio channel embedded in G4P1R PGM OUT"
		::= { ham3000c02v1Entry 243 }

		-- 1.3.6.1.4.1.10106.3.101291.1.1.245
		ham3000c02v1PhaseG4p1r OBJECT-TYPE
			SYNTAX Bit0Nor1Inv
			MAX-ACCESS read-write
			STATUS current
			DESCRIPTION
				"Phase gain applied to the digital audio channel embedded in G4P1R PGM OUT"
		::= { ham3000c02v1Entry 245 }

		-- 1.3.6.1.4.1.10106.3.101291.1.1.247
		ham3000c02v1GanAes1l OBJECT-TYPE
			SYNTAX Gain24dbMute
			MAX-ACCESS read-write
			STATUS current
			DESCRIPTION
				"Gain applied to the digital audio channel output AES1L OUT"
		::= { ham3000c02v1Entry 247 }

		-- 1.3.6.1.4.1.10106.3.101291.1.1.249
		ham3000c02v1PhaseAes1l OBJECT-TYPE
			SYNTAX Bit0Nor1Inv
			MAX-ACCESS read-write
			STATUS current
			DESCRIPTION
				"Phase gain applied to the digital audio channel output AES1L OUT"
		::= { ham3000c02v1Entry 249 }

		-- 1.3.6.1.4.1.10106.3.101291.1.1.251
		ham3000c02v1GanAes1r OBJECT-TYPE
			SYNTAX Gain24dbMute
			MAX-ACCESS read-write
			STATUS current
			DESCRIPTION
				"Gain applied to the digital audio channel output AES1R OUT"
		::= { ham3000c02v1Entry 251 }

		-- 1.3.6.1.4.1.10106.3.101291.1.1.253
		ham3000c02v1PhaseAes1r OBJECT-TYPE
			SYNTAX Bit0Nor1Inv
			MAX-ACCESS read-write
			STATUS current
			DESCRIPTION
				"Phase gain applied to the digital audio channel output AES1R OUT"
		::= { ham3000c02v1Entry 253 }

		-- 1.3.6.1.4.1.10106.3.101291.1.1.255
		ham3000c02v1GanAes2l OBJECT-TYPE
			SYNTAX Gain24dbMute
			MAX-ACCESS read-write
			STATUS current
			DESCRIPTION
				"Gain applied to the digital audio channel output AES2L OUT"
		::= { ham3000c02v1Entry 255 }

		-- 1.3.6.1.4.1.10106.3.101291.1.1.257
		ham3000c02v1PhaseAes2l OBJECT-TYPE
			SYNTAX Bit0Nor1Inv
			MAX-ACCESS read-write
			STATUS current
			DESCRIPTION
				"Phase gain applied to the digital audio channel output AES2L OUT"
		::= { ham3000c02v1Entry 257 }

		-- 1.3.6.1.4.1.10106.3.101291.1.1.259
		ham3000c02v1GanAes2r OBJECT-TYPE
			SYNTAX Gain24dbMute
			MAX-ACCESS read-write
			STATUS current
			DESCRIPTION
				"Gain applied to the digital audio channel output AES2R OUT"
		::= { ham3000c02v1Entry 259 }

		-- 1.3.6.1.4.1.10106.3.101291.1.1.261
		ham3000c02v1PhaseAes2r OBJECT-TYPE
			SYNTAX Bit0Nor1Inv
			MAX-ACCESS read-write
			STATUS current
			DESCRIPTION
				"Phase gain applied to the digital audio channel output AES2R OUT"
		::= { ham3000c02v1Entry 261 }

		-- 1.3.6.1.4.1.10106.3.101291.1.1.263
		ham3000c02v1DelayG1p0l OBJECT-TYPE
			SYNTAX DelayAud
			MAX-ACCESS read-write
			STATUS current
			DESCRIPTION
				"Audio delay in the audio channel embedded in G1P0L PGM OUT"
		::= { ham3000c02v1Entry 263 }

		-- 1.3.6.1.4.1.10106.3.101291.1.1.265
		ham3000c02v1DelayG1p0r OBJECT-TYPE
			SYNTAX DelayAud
			MAX-ACCESS read-write
			STATUS current
			DESCRIPTION
				"Audio delay in the audio channel embedded in G1P0R PGM OUT"
		::= { ham3000c02v1Entry 265 }

		-- 1.3.6.1.4.1.10106.3.101291.1.1.267
		ham3000c02v1DelayG1p1l OBJECT-TYPE
			SYNTAX DelayAud
			MAX-ACCESS read-write
			STATUS current
			DESCRIPTION
				"Audio delay in the audio channel embedded in G1P1L PGM OUT"
		::= { ham3000c02v1Entry 267 }

		-- 1.3.6.1.4.1.10106.3.101291.1.1.269
		ham3000c02v1DelayG1p1r OBJECT-TYPE
			SYNTAX DelayAud
			MAX-ACCESS read-write
			STATUS current
			DESCRIPTION
				"Audio delay in the audio channel embedded in G1P1R PGM OUT"
		::= { ham3000c02v1Entry 269 }

		-- 1.3.6.1.4.1.10106.3.101291.1.1.271
		ham3000c02v1DelayG2p0l OBJECT-TYPE
			SYNTAX DelayAud
			MAX-ACCESS read-write
			STATUS current
			DESCRIPTION
				"Audio delay in the audio channel embedded in G2P0L PGM OUT"
		::= { ham3000c02v1Entry 271 }

		-- 1.3.6.1.4.1.10106.3.101291.1.1.273
		ham3000c02v1DelayG2p0r OBJECT-TYPE
			SYNTAX DelayAud
			MAX-ACCESS read-write
			STATUS current
			DESCRIPTION
				"Audio delay in the audio channel embedded in G2P1R PGM OUT"
		::= { ham3000c02v1Entry 273 }

		-- 1.3.6.1.4.1.10106.3.101291.1.1.275
		ham3000c02v1DelayG2p1l OBJECT-TYPE
			SYNTAX DelayAud
			MAX-ACCESS read-write
			STATUS current
			DESCRIPTION
				"Audio delay in the audio channel embedded in G2P1L PGM OUT"
		::= { ham3000c02v1Entry 275 }

		-- 1.3.6.1.4.1.10106.3.101291.1.1.277
		ham3000c02v1DelayG2p1r OBJECT-TYPE
			SYNTAX DelayAud
			MAX-ACCESS read-write
			STATUS current
			DESCRIPTION
				"Audio delay in the audio channel embedded in G2P1R PGM OUT"
		::= { ham3000c02v1Entry 277 }

		-- 1.3.6.1.4.1.10106.3.101291.1.1.279
		ham3000c02v1DelayG3p0l OBJECT-TYPE
			SYNTAX DelayAud
			MAX-ACCESS read-write
			STATUS current
			DESCRIPTION
				"Audio delay in the audio channel embedded in G3P0L PGM OUT"
		::= { ham3000c02v1Entry 279 }

		-- 1.3.6.1.4.1.10106.3.101291.1.1.281
		ham3000c02v1DelayG3p0r OBJECT-TYPE
			SYNTAX DelayAud
			MAX-ACCESS read-write
			STATUS current
			DESCRIPTION
				"Audio delay in the audio channel embedded in G3P0R PGM OUT"
		::= { ham3000c02v1Entry 281 }

		-- 1.3.6.1.4.1.10106.3.101291.1.1.283
		ham3000c02v1DelayG3p1l OBJECT-TYPE
			SYNTAX DelayAud
			MAX-ACCESS read-write
			STATUS current
			DESCRIPTION
				"Audio delay in the audio channel embedded in G3P1L PGM OUT"
		::= { ham3000c02v1Entry 283 }

		-- 1.3.6.1.4.1.10106.3.101291.1.1.285
		ham3000c02v1DelayG3p1r OBJECT-TYPE
			SYNTAX DelayAud
			MAX-ACCESS read-write
			STATUS current
			DESCRIPTION
				"Audio delay in the audio channel embedded in G3P1R PGM OUT"
		::= { ham3000c02v1Entry 285 }

		-- 1.3.6.1.4.1.10106.3.101291.1.1.287
		ham3000c02v1DelayG4p0l OBJECT-TYPE
			SYNTAX DelayAud
			MAX-ACCESS read-write
			STATUS current
			DESCRIPTION
				"Audio delay in the audio channel embedded in G4P0L PGM OUT"
		::= { ham3000c02v1Entry 287 }

		-- 1.3.6.1.4.1.10106.3.101291.1.1.289
		ham3000c02v1DelayG4p0r OBJECT-TYPE
			SYNTAX DelayAud
			MAX-ACCESS read-write
			STATUS current
			DESCRIPTION
				"Audio delay in the audio channel embedded in G4P0R PGM OUT"
		::= { ham3000c02v1Entry 289 }

		-- 1.3.6.1.4.1.10106.3.101291.1.1.291
		ham3000c02v1DelayG4p1l OBJECT-TYPE
			SYNTAX DelayAud
			MAX-ACCESS read-write
			STATUS current
			DESCRIPTION
				"Audio delay in the audio channel embedded in G4P1L PGM OUT"
		::= { ham3000c02v1Entry 291 }

		-- 1.3.6.1.4.1.10106.3.101291.1.1.293
		ham3000c02v1DelayG4p1r OBJECT-TYPE
			SYNTAX DelayAud
			MAX-ACCESS read-write
			STATUS current
			DESCRIPTION
				"Audio delay in the audio channel embedded in G4P1R PGM OUT"
		::= { ham3000c02v1Entry 293 }

		-- 1.3.6.1.4.1.10106.3.101291.1.1.295
		ham3000c02v1DelayAes1l OBJECT-TYPE
			SYNTAX DelayAud
			MAX-ACCESS read-write
			STATUS current
			DESCRIPTION
				"Audio delay in the digital audio channel AES1L OUT"
		::= { ham3000c02v1Entry 295 }

		-- 1.3.6.1.4.1.10106.3.101291.1.1.297
		ham3000c02v1DelayAes1r OBJECT-TYPE
			SYNTAX DelayAud
			MAX-ACCESS read-write
			STATUS current
			DESCRIPTION
				"Audio delay in the digital audio channel AES1R OUT"
		::= { ham3000c02v1Entry 297 }

		-- 1.3.6.1.4.1.10106.3.101291.1.1.299
		ham3000c02v1DelayAes2l OBJECT-TYPE
			SYNTAX DelayAud
			MAX-ACCESS read-write
			STATUS current
			DESCRIPTION
				"Audio delay in the digital audio channel AES2L OUT"
		::= { ham3000c02v1Entry 299 }

		-- 1.3.6.1.4.1.10106.3.101291.1.1.301
		ham3000c02v1DelayAes2r OBJECT-TYPE
			SYNTAX DelayAud
			MAX-ACCESS read-write
			STATUS current
			DESCRIPTION
				"Audio delay in the digital audio channel AES2R OUT"
		::= { ham3000c02v1Entry 301 }

		-- 1.3.6.1.4.1.10106.3.101291.1.1.303
		ham3000c02v1StatFlash OBJECT-TYPE
			SYNTAX BitFailN
			MAX-ACCESS read-only
			STATUS current
			DESCRIPTION
				"Displays the Flash state"
		::= { ham3000c02v1Entry 303 }

		-- 1.3.6.1.4.1.10106.3.101291.1.1.305
		ham3000c02v1NoSignalMain OBJECT-TYPE
			SYNTAX BitFail
			MAX-ACCESS read-only
			STATUS current
			DESCRIPTION
				"There is no SDI signal or the format is not supported in PGM IN"
		::= { ham3000c02v1Entry 305 }

		-- 1.3.6.1.4.1.10106.3.101291.1.1.306
		ham3000c02v1NoSignalMainTrapEnable OBJECT-TYPE
			SYNTAX AlarmEnable
			MAX-ACCESS read-write
			STATUS current
			DESCRIPTION
				"There is no SDI signal or the format is not supported in PGM IN Trap Enable"
		::= { ham3000c02v1Entry 306 }

		-- 1.3.6.1.4.1.10106.3.101291.1.1.307
		ham3000c02v1UnlockMain OBJECT-TYPE
			SYNTAX BitFail
			MAX-ACCESS read-only
			STATUS current
			DESCRIPTION
				"Indicates signal unlock fail"
		::= { ham3000c02v1Entry 307 }

		-- 1.3.6.1.4.1.10106.3.101291.1.1.308
		ham3000c02v1UnlockMainTrapEnable OBJECT-TYPE
			SYNTAX AlarmEnable
			MAX-ACCESS read-write
			STATUS current
			DESCRIPTION
				"Indicates signal unlock fail Trap Enable"
		::= { ham3000c02v1Entry 308 }

		-- 1.3.6.1.4.1.10106.3.101291.1.1.309
		ham3000c02v1EdhErrorMain OBJECT-TYPE
			SYNTAX BitFail
			MAX-ACCESS read-only
			STATUS current
			DESCRIPTION
				"There are EDH/CRC errors on PGM IN"
		::= { ham3000c02v1Entry 309 }

		-- 1.3.6.1.4.1.10106.3.101291.1.1.310
		ham3000c02v1EdhErrorMainTrapEnable OBJECT-TYPE
			SYNTAX AlarmEnable
			MAX-ACCESS read-write
			STATUS current
			DESCRIPTION
				"There are EDH/CRC errors on PGM IN Trap Enable"
		::= { ham3000c02v1Entry 310 }

		-- 1.3.6.1.4.1.10106.3.101291.1.1.311
		ham3000c02v1NoSignalAux OBJECT-TYPE
			SYNTAX BitFail
			MAX-ACCESS read-only
			STATUS current
			DESCRIPTION
				"There is no SDI signal or the format is not supported in AUX IN"
		::= { ham3000c02v1Entry 311 }

		-- 1.3.6.1.4.1.10106.3.101291.1.1.313
		ham3000c02v1UnlockAux OBJECT-TYPE
			SYNTAX BitFail
			MAX-ACCESS read-only
			STATUS current
			DESCRIPTION
				"Indicates signal AUX IN unlock fail"
		::= { ham3000c02v1Entry 313 }

		-- 1.3.6.1.4.1.10106.3.101291.1.1.315
		ham3000c02v1EdhErrorAux OBJECT-TYPE
			SYNTAX BitFail
			MAX-ACCESS read-only
			STATUS current
			DESCRIPTION
				"There are EDH/CRC errors on AUX IN signal"
		::= { ham3000c02v1Entry 315 }

		-- 1.3.6.1.4.1.10106.3.101291.1.1.317
		ham3000c02v1RefAbsent OBJECT-TYPE
			SYNTAX BitFail
			MAX-ACCESS read-only
			STATUS current
			DESCRIPTION
				"There is no reference signal"
		::= { ham3000c02v1Entry 317 }

		-- 1.3.6.1.4.1.10106.3.101291.1.1.318
		ham3000c02v1RefAbsentTrapEnable OBJECT-TYPE
			SYNTAX AlarmEnable
			MAX-ACCESS read-write
			STATUS current
			DESCRIPTION
				"There is no reference signal Trap Enable"
		::= { ham3000c02v1Entry 318 }

		-- 1.3.6.1.4.1.10106.3.101291.1.1.319
		ham3000c02v1RefUnlock OBJECT-TYPE
			SYNTAX BitFail
			MAX-ACCESS read-only
			STATUS current
			DESCRIPTION
				"Reference input unlock fail"
		::= { ham3000c02v1Entry 319 }

		-- 1.3.6.1.4.1.10106.3.101291.1.1.320
		ham3000c02v1RefUnlockTrapEnable OBJECT-TYPE
			SYNTAX AlarmEnable
			MAX-ACCESS read-write
			STATUS current
			DESCRIPTION
				"Reference input unlock fail Trap Enable"
		::= { ham3000c02v1Entry 320 }

		-- 1.3.6.1.4.1.10106.3.101291.1.1.321
		ham3000c02v1FormatMainIn OBJECT-TYPE
			SYNTAX SdiHd3gFmt3
			MAX-ACCESS read-only
			STATUS current
			DESCRIPTION
				"Indicates the SDI received signal format"
		::= { ham3000c02v1Entry 321 }

		-- 1.3.6.1.4.1.10106.3.101291.1.1.323
		ham3000c02v1FormatAuxIn OBJECT-TYPE
			SYNTAX SdiHd3gFmt3
			MAX-ACCESS read-only
			STATUS current
			DESCRIPTION
				"Indicates the SDI_AUX received signal format"
		::= { ham3000c02v1Entry 323 }

		-- 1.3.6.1.4.1.10106.3.101291.1.1.325
		ham3000c02v1FormatRef OBJECT-TYPE
			SYNTAX SdiHd3gFmt3
			MAX-ACCESS read-only
			STATUS current
			DESCRIPTION
				"Indicates the input reference signal format"
		::= { ham3000c02v1Entry 325 }

		-- 1.3.6.1.4.1.10106.3.101291.1.1.327
		ham3000c02v1FormatMainTx OBJECT-TYPE
			SYNTAX SdiHd3gFmt3
			MAX-ACCESS read-only
			STATUS current
			DESCRIPTION
				"Indicates the SDI transmited signal format"
		::= { ham3000c02v1Entry 327 }

		-- 1.3.6.1.4.1.10106.3.101291.1.1.329
		ham3000c02v1SigDelay OBJECT-TYPE
			SYNTAX DelayX20Us
			MAX-ACCESS read-only
			STATUS current
			DESCRIPTION
				"Indicates the input to output delay"
		::= { ham3000c02v1Entry 329 }

		-- 1.3.6.1.4.1.10106.3.101291.1.1.331
		ham3000c02v1Gr1MainPres OBJECT-TYPE
			SYNTAX Bit0No1Yes
			MAX-ACCESS read-only
			STATUS current
			DESCRIPTION
				"Indicates group 1 presence in PGM IN"
		::= { ham3000c02v1Entry 331 }

		-- 1.3.6.1.4.1.10106.3.101291.1.1.332
		ham3000c02v1Gr1MainPresTrapEnable OBJECT-TYPE
			SYNTAX AlarmEnable
			MAX-ACCESS read-write
			STATUS current
			DESCRIPTION
				"Indicates group 1 presence in PGM IN Trap Enable"
		::= { ham3000c02v1Entry 332 }

		-- 1.3.6.1.4.1.10106.3.101291.1.1.333
		ham3000c02v1Gr2MainPres OBJECT-TYPE
			SYNTAX Bit0No1Yes
			MAX-ACCESS read-only
			STATUS current
			DESCRIPTION
				"Indicates group 2 presence in PGM IN"
		::= { ham3000c02v1Entry 333 }

		-- 1.3.6.1.4.1.10106.3.101291.1.1.334
		ham3000c02v1Gr2MainPresTrapEnable OBJECT-TYPE
			SYNTAX AlarmEnable
			MAX-ACCESS read-write
			STATUS current
			DESCRIPTION
				"Indicates group 2 presence in PGM IN Trap Enable"
		::= { ham3000c02v1Entry 334 }

		-- 1.3.6.1.4.1.10106.3.101291.1.1.335
		ham3000c02v1Gr3MainPres OBJECT-TYPE
			SYNTAX Bit0No1Yes
			MAX-ACCESS read-only
			STATUS current
			DESCRIPTION
				"Indicates group 3 presence in PGM IN"
		::= { ham3000c02v1Entry 335 }

		-- 1.3.6.1.4.1.10106.3.101291.1.1.336
		ham3000c02v1Gr3MainPresTrapEnable OBJECT-TYPE
			SYNTAX AlarmEnable
			MAX-ACCESS read-write
			STATUS current
			DESCRIPTION
				"Indicates group 3 presence in PGM IN Trap Enable"
		::= { ham3000c02v1Entry 336 }

		-- 1.3.6.1.4.1.10106.3.101291.1.1.337
		ham3000c02v1Gr4MainPres OBJECT-TYPE
			SYNTAX Bit0No1Yes
			MAX-ACCESS read-only
			STATUS current
			DESCRIPTION
				"Indicates group 4 presence in PGM IN"
		::= { ham3000c02v1Entry 337 }

		-- 1.3.6.1.4.1.10106.3.101291.1.1.338
		ham3000c02v1Gr4MainPresTrapEnable OBJECT-TYPE
			SYNTAX AlarmEnable
			MAX-ACCESS read-write
			STATUS current
			DESCRIPTION
				"Indicates group 4 presence in PGM IN Trap Enable"
		::= { ham3000c02v1Entry 338 }

		-- 1.3.6.1.4.1.10106.3.101291.1.1.339
		ham3000c02v1Gr1AuxPres OBJECT-TYPE
			SYNTAX Bit0No1Yes
			MAX-ACCESS read-only
			STATUS current
			DESCRIPTION
				"Indicates group 1 presence in AUX IN"
		::= { ham3000c02v1Entry 339 }

		-- 1.3.6.1.4.1.10106.3.101291.1.1.341
		ham3000c02v1Gr2AuxPres OBJECT-TYPE
			SYNTAX Bit0No1Yes
			MAX-ACCESS read-only
			STATUS current
			DESCRIPTION
				"Indicates group 2 presence in AUX IN"
		::= { ham3000c02v1Entry 341 }

		-- 1.3.6.1.4.1.10106.3.101291.1.1.343
		ham3000c02v1Gr3AuxPres OBJECT-TYPE
			SYNTAX Bit0No1Yes
			MAX-ACCESS read-only
			STATUS current
			DESCRIPTION
				"Indicates group 3 presence in AUX IN"
		::= { ham3000c02v1Entry 343 }

		-- 1.3.6.1.4.1.10106.3.101291.1.1.345
		ham3000c02v1Gr4AuxPres OBJECT-TYPE
			SYNTAX Bit0No1Yes
			MAX-ACCESS read-only
			STATUS current
			DESCRIPTION
				"Indicates group 4 presence in AUX IN"
		::= { ham3000c02v1Entry 345 }

		-- 1.3.6.1.4.1.10106.3.101291.1.1.347
		ham3000c02v1Aes1Ok OBJECT-TYPE
			SYNTAX BitFailN
			MAX-ACCESS read-only
			STATUS current
			DESCRIPTION
				"Indicates frame validity of input AES1"
		::= { ham3000c02v1Entry 347 }

		-- 1.3.6.1.4.1.10106.3.101291.1.1.349
		ham3000c02v1Aes1Frq OBJECT-TYPE
			SYNTAX AudioSelFreq6
			MAX-ACCESS read-only
			STATUS current
			DESCRIPTION
				"Indicates sampling frequency of the AES1 input"
		::= { ham3000c02v1Entry 349 }

		-- 1.3.6.1.4.1.10106.3.101291.1.1.351
		ham3000c02v1Aes2Ok OBJECT-TYPE
			SYNTAX BitFailN
			MAX-ACCESS read-only
			STATUS current
			DESCRIPTION
				"Indicates frame validity of input AES2"
		::= { ham3000c02v1Entry 351 }

		-- 1.3.6.1.4.1.10106.3.101291.1.1.353
		ham3000c02v1Aes2Frq OBJECT-TYPE
			SYNTAX AudioSelFreq6
			MAX-ACCESS read-only
			STATUS current
			DESCRIPTION
				"Indicates sampling frequency of the AES2 input"
		::= { ham3000c02v1Entry 353 }

		-- 1.3.6.1.4.1.10106.3.101291.1.1.355
		ham3000c02v1AudStatMain OBJECT-TYPE
			SYNTAX BitFail
			MAX-ACCESS read-only
			STATUS current
			DESCRIPTION
				"Indicates audio fail in audio channels embedded in PGM IN"
		::= { ham3000c02v1Entry 355 }

		-- 1.3.6.1.4.1.10106.3.101291.1.1.356
		ham3000c02v1AudStatMainTrapEnable OBJECT-TYPE
			SYNTAX AlarmEnable
			MAX-ACCESS read-write
			STATUS current
			DESCRIPTION
				"Indicates audio fail in audio channels embedded in PGM IN Trap Enable"
		::= { ham3000c02v1Entry 356 }

		-- 1.3.6.1.4.1.10106.3.101291.1.1.357
		ham3000c02v1AudStatAux OBJECT-TYPE
			SYNTAX BitFail
			MAX-ACCESS read-only
			STATUS current
			DESCRIPTION
				"Indicates audio fail in audio channels embedded in AUX IN"
		::= { ham3000c02v1Entry 357 }

		-- 1.3.6.1.4.1.10106.3.101291.1.1.358
		ham3000c02v1AudStatAuxTrapEnable OBJECT-TYPE
			SYNTAX AlarmEnable
			MAX-ACCESS read-write
			STATUS current
			DESCRIPTION
				"Indicates audio fail in audio channels embedded in AUX IN Trap Enable"
		::= { ham3000c02v1Entry 358 }

		-- 1.3.6.1.4.1.10106.3.101291.1.1.359
		ham3000c02v1AudStatAes1 OBJECT-TYPE
			SYNTAX BitFail
			MAX-ACCESS read-only
			STATUS current
			DESCRIPTION
				"Indicates audio fail in AES1 input"
		::= { ham3000c02v1Entry 359 }

		-- 1.3.6.1.4.1.10106.3.101291.1.1.360
		ham3000c02v1AudStatAes1TrapEnable OBJECT-TYPE
			SYNTAX AlarmEnable
			MAX-ACCESS read-write
			STATUS current
			DESCRIPTION
				"Indicates audio fail in AES1 input Trap Enable"
		::= { ham3000c02v1Entry 360 }

		-- 1.3.6.1.4.1.10106.3.101291.1.1.361
		ham3000c02v1AudStatAes2 OBJECT-TYPE
			SYNTAX BitFail
			MAX-ACCESS read-only
			STATUS current
			DESCRIPTION
				"Indicates audio fail in AES2 input"
		::= { ham3000c02v1Entry 361 }

		-- 1.3.6.1.4.1.10106.3.101291.1.1.362
		ham3000c02v1AudStatAes2TrapEnable OBJECT-TYPE
			SYNTAX AlarmEnable
			MAX-ACCESS read-write
			STATUS current
			DESCRIPTION
				"Indicates audio fail in AES2 input Trap Enable"
		::= { ham3000c02v1Entry 362 }

		-- 1.3.6.1.4.1.10106.3.101291.1.1.363
		ham3000c02v1AudStatAnlg1 OBJECT-TYPE
			SYNTAX BitFail
			MAX-ACCESS read-only
			STATUS current
			DESCRIPTION
				"Indicates audio fail in analogue 1 inputs"
		::= { ham3000c02v1Entry 363 }

		-- 1.3.6.1.4.1.10106.3.101291.1.1.364
		ham3000c02v1AudStatAnlg1TrapEnable OBJECT-TYPE
			SYNTAX AlarmEnable
			MAX-ACCESS read-write
			STATUS current
			DESCRIPTION
				"Indicates audio fail in analogue 1 inputs Trap Enable"
		::= { ham3000c02v1Entry 364 }

		-- 1.3.6.1.4.1.10106.3.101291.1.1.365
		ham3000c02v1AudStatAnlg2 OBJECT-TYPE
			SYNTAX BitFail
			MAX-ACCESS read-only
			STATUS current
			DESCRIPTION
				"Indicates audio fail in analogue 2 inputs"
		::= { ham3000c02v1Entry 365 }

		-- 1.3.6.1.4.1.10106.3.101291.1.1.366
		ham3000c02v1AudStatAnlg2TrapEnable OBJECT-TYPE
			SYNTAX AlarmEnable
			MAX-ACCESS read-write
			STATUS current
			DESCRIPTION
				"Indicates audio fail in analogue 2 inputs Trap Enable"
		::= { ham3000c02v1Entry 366 }

		-- 1.3.6.1.4.1.10106.3.101291.1.1.367
		ham3000c02v1OvldPgmOut OBJECT-TYPE
			SYNTAX BitFail
			MAX-ACCESS read-only
			STATUS current
			DESCRIPTION
				"Indicates audio overload in SDI output PGM OUT"
		::= { ham3000c02v1Entry 367 }

		-- 1.3.6.1.4.1.10106.3.101291.1.1.368
		ham3000c02v1OvldPgmOutTrapEnable OBJECT-TYPE
			SYNTAX AlarmEnable
			MAX-ACCESS read-write
			STATUS current
			DESCRIPTION
				"Indicates audio overload in SDI output PGM OUT Trap Enable"
		::= { ham3000c02v1Entry 368 }

		-- 1.3.6.1.4.1.10106.3.101291.1.1.369
		ham3000c02v1OvldAes1Out OBJECT-TYPE
			SYNTAX BitFail
			MAX-ACCESS read-only
			STATUS current
			DESCRIPTION
				"Indicates audio overload in AES1 OUT"
		::= { ham3000c02v1Entry 369 }

		-- 1.3.6.1.4.1.10106.3.101291.1.1.370
		ham3000c02v1OvldAes1OutTrapEnable OBJECT-TYPE
			SYNTAX AlarmEnable
			MAX-ACCESS read-write
			STATUS current
			DESCRIPTION
				"Indicates audio overload in AES1 OUT Trap Enable"
		::= { ham3000c02v1Entry 370 }

		-- 1.3.6.1.4.1.10106.3.101291.1.1.371
		ham3000c02v1OvldAes2Out OBJECT-TYPE
			SYNTAX BitFail
			MAX-ACCESS read-only
			STATUS current
			DESCRIPTION
				"Indicates audio overload in AES2 OUT"
		::= { ham3000c02v1Entry 371 }

		-- 1.3.6.1.4.1.10106.3.101291.1.1.372
		ham3000c02v1OvldAes2OutTrapEnable OBJECT-TYPE
			SYNTAX AlarmEnable
			MAX-ACCESS read-write
			STATUS current
			DESCRIPTION
				"Indicates audio overload in AES2 OUT Trap Enable"
		::= { ham3000c02v1Entry 372 }

		-- 1.3.6.1.4.1.10106.3.101291.1.1.373
		ham3000c02v1SilPgmOut OBJECT-TYPE
			SYNTAX BitFail
			MAX-ACCESS read-only
			STATUS current
			DESCRIPTION
				"Indicates audio silence in SDI_PGM_OUT"
		::= { ham3000c02v1Entry 373 }

		-- 1.3.6.1.4.1.10106.3.101291.1.1.374
		ham3000c02v1SilPgmOutTrapEnable OBJECT-TYPE
			SYNTAX AlarmEnable
			MAX-ACCESS read-write
			STATUS current
			DESCRIPTION
				"Indicates audio silence in SDI_PGM_OUT Trap Enable"
		::= { ham3000c02v1Entry 374 }

		-- 1.3.6.1.4.1.10106.3.101291.1.1.375
		ham3000c02v1SilAes1Out OBJECT-TYPE
			SYNTAX BitFail
			MAX-ACCESS read-only
			STATUS current
			DESCRIPTION
				"Indicates audio silence in AES1_OUT"
		::= { ham3000c02v1Entry 375 }

		-- 1.3.6.1.4.1.10106.3.101291.1.1.376
		ham3000c02v1SilAes1OutTrapEnable OBJECT-TYPE
			SYNTAX AlarmEnable
			MAX-ACCESS read-write
			STATUS current
			DESCRIPTION
				"Indicates audio silence in AES1_OUT Trap Enable"
		::= { ham3000c02v1Entry 376 }

		-- 1.3.6.1.4.1.10106.3.101291.1.1.377
		ham3000c02v1SilAes2Out OBJECT-TYPE
			SYNTAX BitFail
			MAX-ACCESS read-only
			STATUS current
			DESCRIPTION
				"Indicates audio silence in AES2_OUT"
		::= { ham3000c02v1Entry 377 }

		-- 1.3.6.1.4.1.10106.3.101291.1.1.378
		ham3000c02v1SilAes2OutTrapEnable OBJECT-TYPE
			SYNTAX AlarmEnable
			MAX-ACCESS read-write
			STATUS current
			DESCRIPTION
				"Indicates audio silence in AES2_OUT Trap Enable"
		::= { ham3000c02v1Entry 378 }

		-- 1.3.6.1.4.1.10106.3.101291.1.1.379
		ham3000c02v1SerialNo OBJECT-TYPE
			SYNTAX SerialNo
			MAX-ACCESS read-only
			STATUS current
			DESCRIPTION
				"Serial number"
		::= { ham3000c02v1Entry 379 }

		-- 1.3.6.1.4.1.10106.3.101291.1.1.381
		ham3000c02v1SavePreset OBJECT-TYPE
			SYNTAX Preset16Save
			MAX-ACCESS read-write
			STATUS current
			DESCRIPTION
				"Allows saving a preset"
		::= { ham3000c02v1Entry 381 }

		-- 1.3.6.1.4.1.10106.3.101291.1.1.383
		ham3000c02v1VidAuxSel OBJECT-TYPE
			SYNTAX Bit0Aux1Pgm
			MAX-ACCESS read-write
			STATUS current
			DESCRIPTION
				"Allows selecting the auxiliar input beetween the AUX IN and the PGM IN"
		::= { ham3000c02v1Entry 383 }

		-- 1.3.6.1.4.1.10106.3.407701
		ham3000c03v1 OBJECT IDENTIFIER ::= { albalaProducts 407701 }

		-- 1.3.6.1.4.1.10106.3.407701.1
		ham3000c03v1Table  OBJECT-TYPE
			SYNTAX SEQUENCE OF Ham3000c03v1Entry
			MAX-ACCESS not-accessible
			STATUS current
			DESCRIPTION
				"Module  HAM3000C03V1 Table"
			::= { ham3000c03v1 1 }

		-- 1.3.6.1.4.1.10106.3.407701.1.1
		ham3000c03v1Entry  OBJECT-TYPE
			SYNTAX Ham3000c03v1Entry
			MAX-ACCESS not-accessible
			STATUS current
			DESCRIPTION
				"Module HAM3000C03V1 Entry"
			INDEX { ham3000c03v1Index }
			::= { ham3000c03v1Table 1 }

			Ham3000c03v1Entry ::=
			SEQUENCE {
				ham3000c03v1Index
				ModuleIndex,
				ham3000c03v1ActivePreset
				Preset16Active,
				ham3000c03v1LoadPreset
				Preset16Load,
				ham3000c03v1SynchroMode
				Bit0Fra1Lin,
				ham3000c03v1FailMode
				Bit0Fre1Blk,
				ham3000c03v1DelayMode
				Bit0Syn1De2,
				ham3000c03v1HDelay
				DelayPixel5,
				ham3000c03v1FrameDelay
				DelayFram5,
				ham3000c03v1VDelay
				DelayLines2,
				ham3000c03v1MuxAuxC1
				AudioMxInput6,
				ham3000c03v1MuxAuxC2
				AudioMxInput6,
				ham3000c03v1MuxAuxC3
				AudioMxInput6,
				ham3000c03v1MuxAuxC4
				AudioMxInput6,
				ham3000c03v1FullScaleLev
				LevelDbu,
				ham3000c03v1OvldLevel
				LevelDbfs4,
				ham3000c03v1SilenceLevel
				LevelDbfs3,
				ham3000c03v1SilenceTime
				TimeS2,
				ham3000c03v1Gen1PipsTone
				Bit0Pips1Wav,
				ham3000c03v1Gen2PipsTone
				Bit0Pips1Wav,
				ham3000c03v1MediasGen1
				BitMask,
				ham3000c03v1MediasGen2
				BitMask,
				ham3000c03v1FreqPips1
				FrqGen,
				ham3000c03v1FreqPips2
				FrqGen,
				ham3000c03v1LevelPips1
				LevelDbfsD,
				ham3000c03v1LevelPips2
				LevelDbfsD,
				ham3000c03v1NPipsHour
				Uint4,
				ham3000c03v1NPipsHalf
				Uint4,
				ham3000c03v1ShortPerHour
				TimeX100Ms,
				ham3000c03v1ShortPerHalf
				TimeX100Ms,
				ham3000c03v1LongPerHour
				TimeX100Ms,
				ham3000c03v1LongPerHalf
				TimeX100Ms,
				ham3000c03v1EmbG1p0l
				AudioMxInputA,
				ham3000c03v1EmbG1p0lMonPh
				Bit0Nor1Inv,
				ham3000c03v1EmbG1p0lMono
				BitMask,
				ham3000c03v1EmbG1p0r
				AudioMxInputA,
				ham3000c03v1EmbG1p0rMonPh
				Bit0Nor1Inv,
				ham3000c03v1EmbG1p0rMono
				BitMask,
				ham3000c03v1EmbG1p1l
				AudioMxInputA,
				ham3000c03v1EmbG1p1lMonPh
				Bit0Nor1Inv,
				ham3000c03v1EmbG1p1lMono
				BitMask,
				ham3000c03v1EmbG1p1r
				AudioMxInputA,
				ham3000c03v1EmbG1p1rMonPh
				Bit0Nor1Inv,
				ham3000c03v1EmbG1p1rMono
				BitMask,
				ham3000c03v1EmbG2p0l
				AudioMxInputA,
				ham3000c03v1EmbG2p0lMonPh
				Bit0Nor1Inv,
				ham3000c03v1EmbG2p0lMono
				BitMask,
				ham3000c03v1EmbG2p0r
				AudioMxInputA,
				ham3000c03v1EmbG2p0rMonPh
				Bit0Nor1Inv,
				ham3000c03v1EmbG2p0rMono
				BitMask,
				ham3000c03v1EmbG2p1l
				AudioMxInputA,
				ham3000c03v1EmbG2p1lMonPh
				Bit0Nor1Inv,
				ham3000c03v1EmbG2p1lMono
				BitMask,
				ham3000c03v1EmbG2p1r
				AudioMxInputA,
				ham3000c03v1EmbG2p1rMonPh
				Bit0Nor1Inv,
				ham3000c03v1EmbG2p1rMono
				BitMask,
				ham3000c03v1EmbG3p0l
				AudioMxInputA,
				ham3000c03v1EmbG3p0lMonPh
				Bit0Nor1Inv,
				ham3000c03v1EmbG3p0lMono
				BitMask,
				ham3000c03v1EmbG3p0r
				AudioMxInputA,
				ham3000c03v1EmbG3p0rMonPh
				Bit0Nor1Inv,
				ham3000c03v1EmbG3p0rMono
				BitMask,
				ham3000c03v1EmbG3p1l
				AudioMxInputA,
				ham3000c03v1EmbG3p1lMonPh
				Bit0Nor1Inv,
				ham3000c03v1EmbG3p1lMono
				BitMask,
				ham3000c03v1EmbG3p1r
				AudioMxInputA,
				ham3000c03v1EmbG3p1rMonPh
				Bit0Nor1Inv,
				ham3000c03v1EmbG3p1rMono
				BitMask,
				ham3000c03v1EmbG4p0l
				AudioMxInputA,
				ham3000c03v1EmbG4p0lMonPh
				Bit0Nor1Inv,
				ham3000c03v1EmbG4p0lMono
				BitMask,
				ham3000c03v1EmbG4p0r
				AudioMxInputA,
				ham3000c03v1EmbG4p0rMonPh
				Bit0Nor1Inv,
				ham3000c03v1EmbG4p0rMono
				BitMask,
				ham3000c03v1EmbG4p1l
				AudioMxInputA,
				ham3000c03v1EmbG4p1lMonPh
				Bit0Nor1Inv,
				ham3000c03v1EmbG4p1lMono
				BitMask,
				ham3000c03v1EmbG4p1r
				AudioMxInputA,
				ham3000c03v1EmbG4p1rMonPh
				Bit0Nor1Inv,
				ham3000c03v1EmbG4p1rMono
				BitMask,
				ham3000c03v1AesOut1L
				AudioMxInputA,
				ham3000c03v1AesOut1lMonPh
				Bit0Nor1Inv,
				ham3000c03v1AesOut1lMono
				BitMask,
				ham3000c03v1AesOut1R
				AudioMxInputA,
				ham3000c03v1AesOut1rMonPh
				Bit0Nor1Inv,
				ham3000c03v1AesOut1rMono
				BitMask,
				ham3000c03v1AesOut2L
				AudioMxInputA,
				ham3000c03v1AesOut2lMonPh
				Bit0Nor1Inv,
				ham3000c03v1AesOut2lMono
				BitMask,
				ham3000c03v1AesOut2R
				AudioMxInputA,
				ham3000c03v1AesOut2rMonPh
				Bit0Nor1Inv,
				ham3000c03v1AesOut2rMono
				BitMask,
				ham3000c03v1AnalogOut1L
				AudioMxInputA,
				ham3000c03v1AnlOut1lMonPh
				Bit0Nor1Inv,
				ham3000c03v1AnlgOut1lMono
				BitMask,
				ham3000c03v1AnalogOut1R
				AudioMxInputA,
				ham3000c03v1AnlOut1rMonPh
				Bit0Nor1Inv,
				ham3000c03v1AnlgOut1rMono
				BitMask,
				ham3000c03v1AnalogOut2L
				AudioMxInputA,
				ham3000c03v1AnlOut2lMonPh
				Bit0Nor1Inv,
				ham3000c03v1AnlgOut2lMono
				BitMask,
				ham3000c03v1AnalogOut2R
				AudioMxInputA,
				ham3000c03v1AnlOut2rMonPh
				Bit0Nor1Inv,
				ham3000c03v1AnlgOut2rMono
				BitMask,
				ham3000c03v1GanG1p0l
				Gain24dbMute,
				ham3000c03v1PhaseG1p0l
				Bit0Nor1Inv,
				ham3000c03v1GanG1p0r
				Gain24dbMute,
				ham3000c03v1PhaseG1p0r
				Bit0Nor1Inv,
				ham3000c03v1GanG1p1l
				Gain24dbMute,
				ham3000c03v1PhaseG1p1l
				Bit0Nor1Inv,
				ham3000c03v1GanG1p1r
				Gain24dbMute,
				ham3000c03v1PhaseG1p1r
				Bit0Nor1Inv,
				ham3000c03v1GanG2p0l
				Gain24dbMute,
				ham3000c03v1PhaseG2p0l
				Bit0Nor1Inv,
				ham3000c03v1GanG2p0r
				Gain24dbMute,
				ham3000c03v1PhaseG2p0r
				Bit0Nor1Inv,
				ham3000c03v1GanG2p1l
				Gain24dbMute,
				ham3000c03v1PhaseG2p1l
				Bit0Nor1Inv,
				ham3000c03v1GanG2p1r
				Gain24dbMute,
				ham3000c03v1PhaseG2p1r
				Bit0Nor1Inv,
				ham3000c03v1GanG3p0l
				Gain24dbMute,
				ham3000c03v1PhaseG3p0l
				Bit0Nor1Inv,
				ham3000c03v1GanG3p0r
				Gain24dbMute,
				ham3000c03v1PhaseG3p0r
				Bit0Nor1Inv,
				ham3000c03v1GanG3p1l
				Gain24dbMute,
				ham3000c03v1PhaseG3p1l
				Bit0Nor1Inv,
				ham3000c03v1GanG3p1r
				Gain24dbMute,
				ham3000c03v1PhaseG3p1r
				Bit0Nor1Inv,
				ham3000c03v1GanG4p0l
				Gain24dbMute,
				ham3000c03v1PhaseG4p0l
				Bit0Nor1Inv,
				ham3000c03v1GanG4p0r
				Gain24dbMute,
				ham3000c03v1PhaseG4p0r
				Bit0Nor1Inv,
				ham3000c03v1GanG4p1l
				Gain24dbMute,
				ham3000c03v1PhaseG4p1l
				Bit0Nor1Inv,
				ham3000c03v1GanG4p1r
				Gain24dbMute,
				ham3000c03v1PhaseG4p1r
				Bit0Nor1Inv,
				ham3000c03v1GanAes1l
				Gain24dbMute,
				ham3000c03v1PhaseAes1l
				Bit0Nor1Inv,
				ham3000c03v1GanAes1r
				Gain24dbMute,
				ham3000c03v1PhaseAes1r
				Bit0Nor1Inv,
				ham3000c03v1GanAes2l
				Gain24dbMute,
				ham3000c03v1PhaseAes2l
				Bit0Nor1Inv,
				ham3000c03v1GanAes2r
				Gain24dbMute,
				ham3000c03v1PhaseAes2r
				Bit0Nor1Inv,
				ham3000c03v1GanAnlg1l
				Gain24dbMute,
				ham3000c03v1PhaseAnlg1l
				Bit0Nor1Inv,
				ham3000c03v1GanAnlg1r
				Gain24dbMute,
				ham3000c03v1PhaseAnlg1r
				Bit0Nor1Inv,
				ham3000c03v1GanAnlg2l
				Gain24dbMute,
				ham3000c03v1PhaseAnlg2l
				Bit0Nor1Inv,
				ham3000c03v1GanAnlg2r
				Gain24dbMute,
				ham3000c03v1PhaseAnlg2r
				Bit0Nor1Inv,
				ham3000c03v1DelayG1p0l
				DelayAud,
				ham3000c03v1DelayG1p0r
				DelayAud,
				ham3000c03v1DelayG1p1l
				DelayAud,
				ham3000c03v1DelayG1p1r
				DelayAud,
				ham3000c03v1DelayG2p0l
				DelayAud,
				ham3000c03v1DelayG2p0r
				DelayAud,
				ham3000c03v1DelayG2p1l
				DelayAud,
				ham3000c03v1DelayG2p1r
				DelayAud,
				ham3000c03v1DelayG3p0l
				DelayAud,
				ham3000c03v1DelayG3p0r
				DelayAud,
				ham3000c03v1DelayG3p1l
				DelayAud,
				ham3000c03v1DelayG3p1r
				DelayAud,
				ham3000c03v1DelayG4p0l
				DelayAud,
				ham3000c03v1DelayG4p0r
				DelayAud,
				ham3000c03v1DelayG4p1l
				DelayAud,
				ham3000c03v1DelayG4p1r
				DelayAud,
				ham3000c03v1DelayAes1l
				DelayAud,
				ham3000c03v1DelayAes1r
				DelayAud,
				ham3000c03v1DelayAes2l
				DelayAud,
				ham3000c03v1DelayAes2r
				DelayAud,
				ham3000c03v1DelayAnlg1l
				DelayAud,
				ham3000c03v1DelayAnlg1r
				DelayAud,
				ham3000c03v1DelayAnlg2l
				DelayAud,
				ham3000c03v1DelayAnlg2r
				DelayAud,
				ham3000c03v1StatFlash
				BitFailN,
				ham3000c03v1NoSignalMain
				BitFail,
				ham3000c03v1NoSignalMainTrapEnable
				AlarmEnable,
				ham3000c03v1UnlockMain
				BitFail,
				ham3000c03v1UnlockMainTrapEnable
				AlarmEnable,
				ham3000c03v1EdhErrorMain
				BitFail,
				ham3000c03v1EdhErrorMainTrapEnable
				AlarmEnable,
				ham3000c03v1NoSignalAux
				BitFail,
				ham3000c03v1UnlockAux
				BitFail,
				ham3000c03v1EdhErrorAux
				BitFail,
				ham3000c03v1RefAbsent
				BitFail,
				ham3000c03v1RefAbsentTrapEnable
				AlarmEnable,
				ham3000c03v1RefUnlock
				BitFail,
				ham3000c03v1RefUnlockTrapEnable
				AlarmEnable,
				ham3000c03v1FormatMainIn
				SdiHd3gFmt3,
				ham3000c03v1FormatAuxIn
				SdiHd3gFmt3,
				ham3000c03v1FormatRef
				SdiHd3gFmt3,
				ham3000c03v1FormatMainTx
				SdiHd3gFmt3,
				ham3000c03v1SigDelay
				DelayX20Us,
				ham3000c03v1Gr1MainPres
				Bit0No1Yes,
				ham3000c03v1Gr1MainPresTrapEnable
				AlarmEnable,
				ham3000c03v1Gr2MainPres
				Bit0No1Yes,
				ham3000c03v1Gr2MainPresTrapEnable
				AlarmEnable,
				ham3000c03v1Gr3MainPres
				Bit0No1Yes,
				ham3000c03v1Gr3MainPresTrapEnable
				AlarmEnable,
				ham3000c03v1Gr4MainPres
				Bit0No1Yes,
				ham3000c03v1Gr4MainPresTrapEnable
				AlarmEnable,
				ham3000c03v1Gr1AuxPres
				Bit0No1Yes,
				ham3000c03v1Gr2AuxPres
				Bit0No1Yes,
				ham3000c03v1Gr3AuxPres
				Bit0No1Yes,
				ham3000c03v1Gr4AuxPres
				Bit0No1Yes,
				ham3000c03v1Aes1Ok
				BitFailN,
				ham3000c03v1Aes1Frq
				AudioSelFreq6,
				ham3000c03v1Aes2Ok
				BitFailN,
				ham3000c03v1Aes2Frq
				AudioSelFreq6,
				ham3000c03v1AudStatMain
				BitFail,
				ham3000c03v1AudStatMainTrapEnable
				AlarmEnable,
				ham3000c03v1AudStatAux
				BitFail,
				ham3000c03v1AudStatAuxTrapEnable
				AlarmEnable,
				ham3000c03v1AudStatAes1
				BitFail,
				ham3000c03v1AudStatAes1TrapEnable
				AlarmEnable,
				ham3000c03v1AudStatAes2
				BitFail,
				ham3000c03v1AudStatAes2TrapEnable
				AlarmEnable,
				ham3000c03v1OvldPgmOut
				BitFail,
				ham3000c03v1OvldPgmOutTrapEnable
				AlarmEnable,
				ham3000c03v1OvldAes1Out
				BitFail,
				ham3000c03v1OvldAes1OutTrapEnable
				AlarmEnable,
				ham3000c03v1OvldAes2Out
				BitFail,
				ham3000c03v1OvldAes2OutTrapEnable
				AlarmEnable,
				ham3000c03v1OvldAnlg1Out
				BitFail,
				ham3000c03v1OvldAnlg1OutTrapEnable
				AlarmEnable,
				ham3000c03v1OvldAnlg2Out
				BitFail,
				ham3000c03v1OvldAnlg2OutTrapEnable
				AlarmEnable,
				ham3000c03v1SilPgmOut
				BitFail,
				ham3000c03v1SilPgmOutTrapEnable
				AlarmEnable,
				ham3000c03v1SilAes1Out
				BitFail,
				ham3000c03v1SilAes1OutTrapEnable
				AlarmEnable,
				ham3000c03v1SilAes2Out
				BitFail,
				ham3000c03v1SilAes2OutTrapEnable
				AlarmEnable,
				ham3000c03v1SilAnlg1Out
				BitFail,
				ham3000c03v1SilAnlg1OutTrapEnable
				AlarmEnable,
				ham3000c03v1SilAnlg2Out
				BitFail,
				ham3000c03v1SilAnlg2OutTrapEnable
				AlarmEnable,
				ham3000c03v1SerialNo
				SerialNo,
				ham3000c03v1SavePreset
				Preset16Save,
				ham3000c03v1VidAuxSel
				Bit0Aux1Pgm
			 }

		-- 1.3.6.1.4.1.10106.3.101291.1.1.1
		ham3000c03v1Index OBJECT-TYPE
			SYNTAX ModuleIndex
			MAX-ACCESS read-only
			STATUS current
			DESCRIPTION
				"Index of HAM3000C03V1 Table"
		::= { ham3000c03v1Entry 1 }

		-- 1.3.6.1.4.1.10106.3.101291.1.1.3
		ham3000c03v1ActivePreset OBJECT-TYPE
			SYNTAX Preset16Active
			MAX-ACCESS read-only
			STATUS current
			DESCRIPTION
				"Shows the active preset"
		::= { ham3000c03v1Entry 3 }

		-- 1.3.6.1.4.1.10106.3.101291.1.1.5
		ham3000c03v1LoadPreset OBJECT-TYPE
			SYNTAX Preset16Load
			MAX-ACCESS read-write
			STATUS current
			DESCRIPTION
				"Allows loading a preset"
		::= { ham3000c03v1Entry 5 }

		-- 1.3.6.1.4.1.10106.3.101291.1.1.7
		ham3000c03v1SynchroMode OBJECT-TYPE
			SYNTAX Bit0Fra1Lin
			MAX-ACCESS read-write
			STATUS current
			DESCRIPTION
				"Allows selecting the synchronizing mode"
		::= { ham3000c03v1Entry 7 }

		-- 1.3.6.1.4.1.10106.3.101291.1.1.9
		ham3000c03v1FailMode OBJECT-TYPE
			SYNTAX Bit0Fre1Blk
			MAX-ACCESS read-write
			STATUS current
			DESCRIPTION
				"Allows selecting the output video signal if the input fails"
		::= { ham3000c03v1Entry 9 }

		-- 1.3.6.1.4.1.10106.3.101291.1.1.11
		ham3000c03v1DelayMode OBJECT-TYPE
			SYNTAX Bit0Syn1De2
			MAX-ACCESS read-write
			STATUS current
			DESCRIPTION
				"Allows selecting the operating mode"
		::= { ham3000c03v1Entry 11 }

		-- 1.3.6.1.4.1.10106.3.101291.1.1.13
		ham3000c03v1HDelay OBJECT-TYPE
			SYNTAX DelayPixel5
			MAX-ACCESS read-write
			STATUS current
			DESCRIPTION
				"Allows adjusting the video horizontal delay"
		::= { ham3000c03v1Entry 13 }

		-- 1.3.6.1.4.1.10106.3.101291.1.1.15
		ham3000c03v1FrameDelay OBJECT-TYPE
			SYNTAX DelayFram5
			MAX-ACCESS read-write
			STATUS current
			DESCRIPTION
				"Allows adjusting the frame delay"
		::= { ham3000c03v1Entry 15 }

		-- 1.3.6.1.4.1.10106.3.101291.1.1.17
		ham3000c03v1VDelay OBJECT-TYPE
			SYNTAX DelayLines2
			MAX-ACCESS read-write
			STATUS current
			DESCRIPTION
				"Allows adjusting the video vertical delay"
		::= { ham3000c03v1Entry 17 }

		-- 1.3.6.1.4.1.10106.3.101291.1.1.19
		ham3000c03v1MuxAuxC1 OBJECT-TYPE
			SYNTAX AudioMxInput6
			MAX-ACCESS read-write
			STATUS current
			DESCRIPTION
				"Selects the channel 1 from the input video signal AUX IN"
		::= { ham3000c03v1Entry 19 }

		-- 1.3.6.1.4.1.10106.3.101291.1.1.21
		ham3000c03v1MuxAuxC2 OBJECT-TYPE
			SYNTAX AudioMxInput6
			MAX-ACCESS read-write
			STATUS current
			DESCRIPTION
				"Selects the channel 2 from the input video signal AUX IN"
		::= { ham3000c03v1Entry 21 }

		-- 1.3.6.1.4.1.10106.3.101291.1.1.23
		ham3000c03v1MuxAuxC3 OBJECT-TYPE
			SYNTAX AudioMxInput6
			MAX-ACCESS read-write
			STATUS current
			DESCRIPTION
				"Selects the channel 3 from the input video signal AUX IN"
		::= { ham3000c03v1Entry 23 }

		-- 1.3.6.1.4.1.10106.3.101291.1.1.25
		ham3000c03v1MuxAuxC4 OBJECT-TYPE
			SYNTAX AudioMxInput6
			MAX-ACCESS read-write
			STATUS current
			DESCRIPTION
				"Selects the channel 4 from the input video signal AUX IN"
		::= { ham3000c03v1Entry 25 }

		-- 1.3.6.1.4.1.10106.3.101291.1.1.27
		ham3000c03v1FullScaleLev OBJECT-TYPE
			SYNTAX LevelDbu
			MAX-ACCESS read-write
			STATUS current
			DESCRIPTION
				"Full scale level"
		::= { ham3000c03v1Entry 27 }

		-- 1.3.6.1.4.1.10106.3.101291.1.1.29
		ham3000c03v1OvldLevel OBJECT-TYPE
			SYNTAX LevelDbfs4
			MAX-ACCESS read-write
			STATUS current
			DESCRIPTION
				"Allows adjusting the threshold level for the overload detector"
		::= { ham3000c03v1Entry 29 }

		-- 1.3.6.1.4.1.10106.3.101291.1.1.31
		ham3000c03v1SilenceLevel OBJECT-TYPE
			SYNTAX LevelDbfs3
			MAX-ACCESS read-write
			STATUS current
			DESCRIPTION
				"Allows adjusting the threshold level for the silence detector"
		::= { ham3000c03v1Entry 31 }

		-- 1.3.6.1.4.1.10106.3.101291.1.1.33
		ham3000c03v1SilenceTime OBJECT-TYPE
			SYNTAX TimeS2
			MAX-ACCESS read-write
			STATUS current
			DESCRIPTION
				"Allows adjusting the silence time"
		::= { ham3000c03v1Entry 33 }

		-- 1.3.6.1.4.1.10106.3.101291.1.1.35
		ham3000c03v1Gen1PipsTone OBJECT-TYPE
			SYNTAX Bit0Pips1Wav
			MAX-ACCESS read-write
			STATUS current
			DESCRIPTION
				"Selects the type of signal to be generated at channel 1 of the generator: Greenwich Time Signals (Pips) or a sinewave"
		::= { ham3000c03v1Entry 35 }

		-- 1.3.6.1.4.1.10106.3.101291.1.1.37
		ham3000c03v1Gen2PipsTone OBJECT-TYPE
			SYNTAX Bit0Pips1Wav
			MAX-ACCESS read-write
			STATUS current
			DESCRIPTION
				"Selects the type of signal to be generated at channel 2 of the generator: Greenwich Time Signals (Pips) or a sinewave"
		::= { ham3000c03v1Entry 37 }

		-- 1.3.6.1.4.1.10106.3.101291.1.1.39
		ham3000c03v1MediasGen1 OBJECT-TYPE
			SYNTAX BitMask
			MAX-ACCESS read-write
			STATUS current
			DESCRIPTION
				"Enables the pips sounding at half past at channel 1 of the generator"
		::= { ham3000c03v1Entry 39 }

		-- 1.3.6.1.4.1.10106.3.101291.1.1.41
		ham3000c03v1MediasGen2 OBJECT-TYPE
			SYNTAX BitMask
			MAX-ACCESS read-write
			STATUS current
			DESCRIPTION
				"Enables the pips sounding at half past at channel 2 of the generator"
		::= { ham3000c03v1Entry 41 }

		-- 1.3.6.1.4.1.10106.3.101291.1.1.43
		ham3000c03v1FreqPips1 OBJECT-TYPE
			SYNTAX FrqGen
			MAX-ACCESS read-write
			STATUS current
			DESCRIPTION
				"Frequency of the sound signals generated at channel 1"
		::= { ham3000c03v1Entry 43 }

		-- 1.3.6.1.4.1.10106.3.101291.1.1.45
		ham3000c03v1FreqPips2 OBJECT-TYPE
			SYNTAX FrqGen
			MAX-ACCESS read-write
			STATUS current
			DESCRIPTION
				"Frequency of the sound singals generated at channel 2"
		::= { ham3000c03v1Entry 45 }

		-- 1.3.6.1.4.1.10106.3.101291.1.1.47
		ham3000c03v1LevelPips1 OBJECT-TYPE
			SYNTAX LevelDbfsD
			MAX-ACCESS read-write
			STATUS current
			DESCRIPTION
				"Amplitude of the sound signals generated at channel 1"
		::= { ham3000c03v1Entry 47 }

		-- 1.3.6.1.4.1.10106.3.101291.1.1.49
		ham3000c03v1LevelPips2 OBJECT-TYPE
			SYNTAX LevelDbfsD
			MAX-ACCESS read-write
			STATUS current
			DESCRIPTION
				"Amplitude of the sound signals generated at channel 2"
		::= { ham3000c03v1Entry 49 }

		-- 1.3.6.1.4.1.10106.3.101291.1.1.51
		ham3000c03v1NPipsHour OBJECT-TYPE
			SYNTAX Uint4
			MAX-ACCESS read-write
			STATUS current
			DESCRIPTION
				"Number of short pips generated at o'clock"
		::= { ham3000c03v1Entry 51 }

		-- 1.3.6.1.4.1.10106.3.101291.1.1.53
		ham3000c03v1NPipsHalf OBJECT-TYPE
			SYNTAX Uint4
			MAX-ACCESS read-write
			STATUS current
			DESCRIPTION
				"Number of short pips generated at half past"
		::= { ham3000c03v1Entry 53 }

		-- 1.3.6.1.4.1.10106.3.101291.1.1.55
		ham3000c03v1ShortPerHour OBJECT-TYPE
			SYNTAX TimeX100Ms
			MAX-ACCESS read-write
			STATUS current
			DESCRIPTION
				"Length of o'clock short pips"
		::= { ham3000c03v1Entry 55 }

		-- 1.3.6.1.4.1.10106.3.101291.1.1.57
		ham3000c03v1ShortPerHalf OBJECT-TYPE
			SYNTAX TimeX100Ms
			MAX-ACCESS read-write
			STATUS current
			DESCRIPTION
				"Length of half past short pips"
		::= { ham3000c03v1Entry 57 }

		-- 1.3.6.1.4.1.10106.3.101291.1.1.59
		ham3000c03v1LongPerHour OBJECT-TYPE
			SYNTAX TimeX100Ms
			MAX-ACCESS read-write
			STATUS current
			DESCRIPTION
				"Length of o'clock long pip"
		::= { ham3000c03v1Entry 59 }

		-- 1.3.6.1.4.1.10106.3.101291.1.1.61
		ham3000c03v1LongPerHalf OBJECT-TYPE
			SYNTAX TimeX100Ms
			MAX-ACCESS read-write
			STATUS current
			DESCRIPTION
				"Length of half past long pip"
		::= { ham3000c03v1Entry 61 }

		-- 1.3.6.1.4.1.10106.3.101291.1.1.63
		ham3000c03v1EmbG1p0l OBJECT-TYPE
			SYNTAX AudioMxInputA
			MAX-ACCESS read-write
			STATUS current
			DESCRIPTION
				"Audio channel assignment to the audio channel embedded in G1P0L PGM OUT"
		::= { ham3000c03v1Entry 63 }

		-- 1.3.6.1.4.1.10106.3.101291.1.1.65
		ham3000c03v1EmbG1p0lMonPh OBJECT-TYPE
			SYNTAX Bit0Nor1Inv
			MAX-ACCESS read-write
			STATUS current
			DESCRIPTION
				"Phase applied to the secundary channel in the stereophonic audio pair for generating the monophonic audio in G1P0L PGM OUT"
		::= { ham3000c03v1Entry 65 }

		-- 1.3.6.1.4.1.10106.3.101291.1.1.67
		ham3000c03v1EmbG1p0lMono OBJECT-TYPE
			SYNTAX BitMask
			MAX-ACCESS read-write
			STATUS current
			DESCRIPTION
				"Monophonic audio generated from the audio pair assigned to G1P0L PGM OUT"
		::= { ham3000c03v1Entry 67 }

		-- 1.3.6.1.4.1.10106.3.101291.1.1.69
		ham3000c03v1EmbG1p0r OBJECT-TYPE
			SYNTAX AudioMxInputA
			MAX-ACCESS read-write
			STATUS current
			DESCRIPTION
				"Audio channel assignment to the audio channel embedded in G1P0R PGM OUT"
		::= { ham3000c03v1Entry 69 }

		-- 1.3.6.1.4.1.10106.3.101291.1.1.71
		ham3000c03v1EmbG1p0rMonPh OBJECT-TYPE
			SYNTAX Bit0Nor1Inv
			MAX-ACCESS read-write
			STATUS current
			DESCRIPTION
				"Phase applied to the secundary channel in the stereophonic audio pair for generating the monophonic audio in G1P0R PGM OUT"
		::= { ham3000c03v1Entry 71 }

		-- 1.3.6.1.4.1.10106.3.101291.1.1.73
		ham3000c03v1EmbG1p0rMono OBJECT-TYPE
			SYNTAX BitMask
			MAX-ACCESS read-write
			STATUS current
			DESCRIPTION
				"Monophonic audio generated from the audio pair assigned to G1P0R PGM OUT"
		::= { ham3000c03v1Entry 73 }

		-- 1.3.6.1.4.1.10106.3.101291.1.1.75
		ham3000c03v1EmbG1p1l OBJECT-TYPE
			SYNTAX AudioMxInputA
			MAX-ACCESS read-write
			STATUS current
			DESCRIPTION
				"Audio channel assignment to the audio channel embedded in G1P1L PGM OUT"
		::= { ham3000c03v1Entry 75 }

		-- 1.3.6.1.4.1.10106.3.101291.1.1.77
		ham3000c03v1EmbG1p1lMonPh OBJECT-TYPE
			SYNTAX Bit0Nor1Inv
			MAX-ACCESS read-write
			STATUS current
			DESCRIPTION
				"Phase applied to the secundary channel in the stereophonic audio pair for generating the monophonic audio in G1P1L PGM OUT"
		::= { ham3000c03v1Entry 77 }

		-- 1.3.6.1.4.1.10106.3.101291.1.1.79
		ham3000c03v1EmbG1p1lMono OBJECT-TYPE
			SYNTAX BitMask
			MAX-ACCESS read-write
			STATUS current
			DESCRIPTION
				"Monophonic audio generated from the audio pair assigned to G1P1L PGM OUT"
		::= { ham3000c03v1Entry 79 }

		-- 1.3.6.1.4.1.10106.3.101291.1.1.81
		ham3000c03v1EmbG1p1r OBJECT-TYPE
			SYNTAX AudioMxInputA
			MAX-ACCESS read-write
			STATUS current
			DESCRIPTION
				"Audio channel assignment to the audio channel embedded in G1P1R PGM OUT"
		::= { ham3000c03v1Entry 81 }

		-- 1.3.6.1.4.1.10106.3.101291.1.1.83
		ham3000c03v1EmbG1p1rMonPh OBJECT-TYPE
			SYNTAX Bit0Nor1Inv
			MAX-ACCESS read-write
			STATUS current
			DESCRIPTION
				"Phase applied to the secundary channel in the stereophonic audio pair for generating the monophonic audio in G1P1R PGM OUT"
		::= { ham3000c03v1Entry 83 }

		-- 1.3.6.1.4.1.10106.3.101291.1.1.85
		ham3000c03v1EmbG1p1rMono OBJECT-TYPE
			SYNTAX BitMask
			MAX-ACCESS read-write
			STATUS current
			DESCRIPTION
				"Monophonic audio generated from the audio pair assigned to G1P1R PGM OUT"
		::= { ham3000c03v1Entry 85 }

		-- 1.3.6.1.4.1.10106.3.101291.1.1.87
		ham3000c03v1EmbG2p0l OBJECT-TYPE
			SYNTAX AudioMxInputA
			MAX-ACCESS read-write
			STATUS current
			DESCRIPTION
				"Audio channel assignment to the audio channel embedded in G2P0L PGM OUT"
		::= { ham3000c03v1Entry 87 }

		-- 1.3.6.1.4.1.10106.3.101291.1.1.89
		ham3000c03v1EmbG2p0lMonPh OBJECT-TYPE
			SYNTAX Bit0Nor1Inv
			MAX-ACCESS read-write
			STATUS current
			DESCRIPTION
				"Phase applied to the secundary channel in the stereophonic audio pair for generating the monophonic audio in G2P0L PGM OUT"
		::= { ham3000c03v1Entry 89 }

		-- 1.3.6.1.4.1.10106.3.101291.1.1.91
		ham3000c03v1EmbG2p0lMono OBJECT-TYPE
			SYNTAX BitMask
			MAX-ACCESS read-write
			STATUS current
			DESCRIPTION
				"Monophonic audio generated from the audio pair assigned to G2P0L PGM OUT"
		::= { ham3000c03v1Entry 91 }

		-- 1.3.6.1.4.1.10106.3.101291.1.1.93
		ham3000c03v1EmbG2p0r OBJECT-TYPE
			SYNTAX AudioMxInputA
			MAX-ACCESS read-write
			STATUS current
			DESCRIPTION
				"Audio channel assignment to the audio channel embedded in G2P0R PGM OUT"
		::= { ham3000c03v1Entry 93 }

		-- 1.3.6.1.4.1.10106.3.101291.1.1.95
		ham3000c03v1EmbG2p0rMonPh OBJECT-TYPE
			SYNTAX Bit0Nor1Inv
			MAX-ACCESS read-write
			STATUS current
			DESCRIPTION
				"Phase applied to the secundary channel in the stereophonic audio pair for generating the monophonic audio in G2P0R PGM OUT"
		::= { ham3000c03v1Entry 95 }

		-- 1.3.6.1.4.1.10106.3.101291.1.1.97
		ham3000c03v1EmbG2p0rMono OBJECT-TYPE
			SYNTAX BitMask
			MAX-ACCESS read-write
			STATUS current
			DESCRIPTION
				"Monophonic audio generated from the audio pair assigned to G2P0R PGM OUT"
		::= { ham3000c03v1Entry 97 }

		-- 1.3.6.1.4.1.10106.3.101291.1.1.99
		ham3000c03v1EmbG2p1l OBJECT-TYPE
			SYNTAX AudioMxInputA
			MAX-ACCESS read-write
			STATUS current
			DESCRIPTION
				"Audio channel assignment to the audio channel embedded in G2P1L PGM OUT"
		::= { ham3000c03v1Entry 99 }

		-- 1.3.6.1.4.1.10106.3.101291.1.1.101
		ham3000c03v1EmbG2p1lMonPh OBJECT-TYPE
			SYNTAX Bit0Nor1Inv
			MAX-ACCESS read-write
			STATUS current
			DESCRIPTION
				"Phase applied to the secundary channel in the stereophonic audio pair for generating the monophonic audio in G2P1L PGM OUT"
		::= { ham3000c03v1Entry 101 }

		-- 1.3.6.1.4.1.10106.3.101291.1.1.103
		ham3000c03v1EmbG2p1lMono OBJECT-TYPE
			SYNTAX BitMask
			MAX-ACCESS read-write
			STATUS current
			DESCRIPTION
				"Monophonic audio generated from the audio pair assigned to G2P1L PGM OUT"
		::= { ham3000c03v1Entry 103 }

		-- 1.3.6.1.4.1.10106.3.101291.1.1.105
		ham3000c03v1EmbG2p1r OBJECT-TYPE
			SYNTAX AudioMxInputA
			MAX-ACCESS read-write
			STATUS current
			DESCRIPTION
				"Audio channel assignment to the audio channel embedded in G2P1R PGM OUT"
		::= { ham3000c03v1Entry 105 }

		-- 1.3.6.1.4.1.10106.3.101291.1.1.107
		ham3000c03v1EmbG2p1rMonPh OBJECT-TYPE
			SYNTAX Bit0Nor1Inv
			MAX-ACCESS read-write
			STATUS current
			DESCRIPTION
				"Phase applied to the secundary channel in the stereophonic audio pair for generating the monophonic audio in G2P1R PGM OUT"
		::= { ham3000c03v1Entry 107 }

		-- 1.3.6.1.4.1.10106.3.101291.1.1.109
		ham3000c03v1EmbG2p1rMono OBJECT-TYPE
			SYNTAX BitMask
			MAX-ACCESS read-write
			STATUS current
			DESCRIPTION
				"Monophonic audio generated from the audio pair assigned to G2P1R PGM OUT"
		::= { ham3000c03v1Entry 109 }

		-- 1.3.6.1.4.1.10106.3.101291.1.1.111
		ham3000c03v1EmbG3p0l OBJECT-TYPE
			SYNTAX AudioMxInputA
			MAX-ACCESS read-write
			STATUS current
			DESCRIPTION
				"Audio channel assignment to the audio channel embedded in G3P0L PGM OUT"
		::= { ham3000c03v1Entry 111 }

		-- 1.3.6.1.4.1.10106.3.101291.1.1.113
		ham3000c03v1EmbG3p0lMonPh OBJECT-TYPE
			SYNTAX Bit0Nor1Inv
			MAX-ACCESS read-write
			STATUS current
			DESCRIPTION
				"Phase applied to the secundary channel in the stereophonic audio pair for generating the monophonic audio in G3P0L PGM OUT"
		::= { ham3000c03v1Entry 113 }

		-- 1.3.6.1.4.1.10106.3.101291.1.1.115
		ham3000c03v1EmbG3p0lMono OBJECT-TYPE
			SYNTAX BitMask
			MAX-ACCESS read-write
			STATUS current
			DESCRIPTION
				"Monophonic audio generated from the audio pair assigned to G3P0L PGM OUT"
		::= { ham3000c03v1Entry 115 }

		-- 1.3.6.1.4.1.10106.3.101291.1.1.117
		ham3000c03v1EmbG3p0r OBJECT-TYPE
			SYNTAX AudioMxInputA
			MAX-ACCESS read-write
			STATUS current
			DESCRIPTION
				"Audio channel assignment to the audio channel embedded in G3P0R PGM OUT"
		::= { ham3000c03v1Entry 117 }

		-- 1.3.6.1.4.1.10106.3.101291.1.1.119
		ham3000c03v1EmbG3p0rMonPh OBJECT-TYPE
			SYNTAX Bit0Nor1Inv
			MAX-ACCESS read-write
			STATUS current
			DESCRIPTION
				"Phase applied to the secundary channel in the stereophonic audio pair for generating the monophonic audio in G3P0R PGM OUT"
		::= { ham3000c03v1Entry 119 }

		-- 1.3.6.1.4.1.10106.3.101291.1.1.121
		ham3000c03v1EmbG3p0rMono OBJECT-TYPE
			SYNTAX BitMask
			MAX-ACCESS read-write
			STATUS current
			DESCRIPTION
				"Monophonic audio generated from the audio pair assigned to G3P0R PGM OUT"
		::= { ham3000c03v1Entry 121 }

		-- 1.3.6.1.4.1.10106.3.101291.1.1.123
		ham3000c03v1EmbG3p1l OBJECT-TYPE
			SYNTAX AudioMxInputA
			MAX-ACCESS read-write
			STATUS current
			DESCRIPTION
				"Audio channel assignment to the audio channel embedded in G3P1L PGM OUT"
		::= { ham3000c03v1Entry 123 }

		-- 1.3.6.1.4.1.10106.3.101291.1.1.125
		ham3000c03v1EmbG3p1lMonPh OBJECT-TYPE
			SYNTAX Bit0Nor1Inv
			MAX-ACCESS read-write
			STATUS current
			DESCRIPTION
				"Phase applied to the secundary channel in the stereophonic audio pair for generating the monophonic audio in G3P1L PGM OUT"
		::= { ham3000c03v1Entry 125 }

		-- 1.3.6.1.4.1.10106.3.101291.1.1.127
		ham3000c03v1EmbG3p1lMono OBJECT-TYPE
			SYNTAX BitMask
			MAX-ACCESS read-write
			STATUS current
			DESCRIPTION
				"Monophonic audio generated from the audio pair assigned to G3P1L PGM OUT"
		::= { ham3000c03v1Entry 127 }

		-- 1.3.6.1.4.1.10106.3.101291.1.1.129
		ham3000c03v1EmbG3p1r OBJECT-TYPE
			SYNTAX AudioMxInputA
			MAX-ACCESS read-write
			STATUS current
			DESCRIPTION
				"Audio channel assignment to the audio channel embedded in G3P1R PGM OUT"
		::= { ham3000c03v1Entry 129 }

		-- 1.3.6.1.4.1.10106.3.101291.1.1.131
		ham3000c03v1EmbG3p1rMonPh OBJECT-TYPE
			SYNTAX Bit0Nor1Inv
			MAX-ACCESS read-write
			STATUS current
			DESCRIPTION
				"Phase applied to the secundary channel in the stereophonic audio pair for generating the monophonic audio in G3P1R PGM OUT"
		::= { ham3000c03v1Entry 131 }

		-- 1.3.6.1.4.1.10106.3.101291.1.1.133
		ham3000c03v1EmbG3p1rMono OBJECT-TYPE
			SYNTAX BitMask
			MAX-ACCESS read-write
			STATUS current
			DESCRIPTION
				"Monophonic audio generated from the audio pair assigned to G3P1R PGM OUT"
		::= { ham3000c03v1Entry 133 }

		-- 1.3.6.1.4.1.10106.3.101291.1.1.135
		ham3000c03v1EmbG4p0l OBJECT-TYPE
			SYNTAX AudioMxInputA
			MAX-ACCESS read-write
			STATUS current
			DESCRIPTION
				"Audio channel assignment to the audio channel embedded in G4P0L PGM OUT"
		::= { ham3000c03v1Entry 135 }

		-- 1.3.6.1.4.1.10106.3.101291.1.1.137
		ham3000c03v1EmbG4p0lMonPh OBJECT-TYPE
			SYNTAX Bit0Nor1Inv
			MAX-ACCESS read-write
			STATUS current
			DESCRIPTION
				"Phase applied to the secundary channel in the stereophonic audio pair for generating the monophonic audio in G4P0L PGM OUT"
		::= { ham3000c03v1Entry 137 }

		-- 1.3.6.1.4.1.10106.3.101291.1.1.139
		ham3000c03v1EmbG4p0lMono OBJECT-TYPE
			SYNTAX BitMask
			MAX-ACCESS read-write
			STATUS current
			DESCRIPTION
				"Monophonic audio generated from the audio pair assigned to G4P0L PGM OUT"
		::= { ham3000c03v1Entry 139 }

		-- 1.3.6.1.4.1.10106.3.101291.1.1.141
		ham3000c03v1EmbG4p0r OBJECT-TYPE
			SYNTAX AudioMxInputA
			MAX-ACCESS read-write
			STATUS current
			DESCRIPTION
				"Audio channel assignment to the audio channel embedded in G4P0R PGM OUT"
		::= { ham3000c03v1Entry 141 }

		-- 1.3.6.1.4.1.10106.3.101291.1.1.143
		ham3000c03v1EmbG4p0rMonPh OBJECT-TYPE
			SYNTAX Bit0Nor1Inv
			MAX-ACCESS read-write
			STATUS current
			DESCRIPTION
				"Phase applied to the secundary channel in the stereophonic audio pair for generating the monophonic audio in G4P0R PGM OUT"
		::= { ham3000c03v1Entry 143 }

		-- 1.3.6.1.4.1.10106.3.101291.1.1.145
		ham3000c03v1EmbG4p0rMono OBJECT-TYPE
			SYNTAX BitMask
			MAX-ACCESS read-write
			STATUS current
			DESCRIPTION
				"Monophonic audio generated from the audio pair assigned to G4P0R PGM OUT"
		::= { ham3000c03v1Entry 145 }

		-- 1.3.6.1.4.1.10106.3.101291.1.1.147
		ham3000c03v1EmbG4p1l OBJECT-TYPE
			SYNTAX AudioMxInputA
			MAX-ACCESS read-write
			STATUS current
			DESCRIPTION
				"Audio channel assignment to the audio channel embedded in G4P1L PGM OUT"
		::= { ham3000c03v1Entry 147 }

		-- 1.3.6.1.4.1.10106.3.101291.1.1.149
		ham3000c03v1EmbG4p1lMonPh OBJECT-TYPE
			SYNTAX Bit0Nor1Inv
			MAX-ACCESS read-write
			STATUS current
			DESCRIPTION
				"Phase applied to the secundary channel in the stereophonic audio pair for generating the monophonic audio in G4P1L PGM OUT"
		::= { ham3000c03v1Entry 149 }

		-- 1.3.6.1.4.1.10106.3.101291.1.1.151
		ham3000c03v1EmbG4p1lMono OBJECT-TYPE
			SYNTAX BitMask
			MAX-ACCESS read-write
			STATUS current
			DESCRIPTION
				"Monophonic audio generated from the audio pair assigned to G4P1L PGM OUT"
		::= { ham3000c03v1Entry 151 }

		-- 1.3.6.1.4.1.10106.3.101291.1.1.153
		ham3000c03v1EmbG4p1r OBJECT-TYPE
			SYNTAX AudioMxInputA
			MAX-ACCESS read-write
			STATUS current
			DESCRIPTION
				"Audio channel assignment to the audio channel embedded in G4P1R PGM OUT"
		::= { ham3000c03v1Entry 153 }

		-- 1.3.6.1.4.1.10106.3.101291.1.1.155
		ham3000c03v1EmbG4p1rMonPh OBJECT-TYPE
			SYNTAX Bit0Nor1Inv
			MAX-ACCESS read-write
			STATUS current
			DESCRIPTION
				"Phase applied to the secundary channel in the stereophonic audio pair for generating the monophonic audio in G4P1R PGM OUT"
		::= { ham3000c03v1Entry 155 }

		-- 1.3.6.1.4.1.10106.3.101291.1.1.157
		ham3000c03v1EmbG4p1rMono OBJECT-TYPE
			SYNTAX BitMask
			MAX-ACCESS read-write
			STATUS current
			DESCRIPTION
				"Monophonic audio generated from the audio pair assigned to G4P1R PGM OUT"
		::= { ham3000c03v1Entry 157 }

		-- 1.3.6.1.4.1.10106.3.101291.1.1.159
		ham3000c03v1AesOut1L OBJECT-TYPE
			SYNTAX AudioMxInputA
			MAX-ACCESS read-write
			STATUS current
			DESCRIPTION
				"Audio channel assignment to the digital audio output AES1L OUT"
		::= { ham3000c03v1Entry 159 }

		-- 1.3.6.1.4.1.10106.3.101291.1.1.161
		ham3000c03v1AesOut1lMonPh OBJECT-TYPE
			SYNTAX Bit0Nor1Inv
			MAX-ACCESS read-write
			STATUS current
			DESCRIPTION
				"Phase applied to the secundary channel in the stereophonic audio pair for generating the monophonic audio in AES1L OUT"
		::= { ham3000c03v1Entry 161 }

		-- 1.3.6.1.4.1.10106.3.101291.1.1.163
		ham3000c03v1AesOut1lMono OBJECT-TYPE
			SYNTAX BitMask
			MAX-ACCESS read-write
			STATUS current
			DESCRIPTION
				"Monophonic audio generated from the audio pair assigned to AES1L OUT"
		::= { ham3000c03v1Entry 163 }

		-- 1.3.6.1.4.1.10106.3.101291.1.1.165
		ham3000c03v1AesOut1R OBJECT-TYPE
			SYNTAX AudioMxInputA
			MAX-ACCESS read-write
			STATUS current
			DESCRIPTION
				"Audio channel assignment to the digital audio output AES1R OUT"
		::= { ham3000c03v1Entry 165 }

		-- 1.3.6.1.4.1.10106.3.101291.1.1.167
		ham3000c03v1AesOut1rMonPh OBJECT-TYPE
			SYNTAX Bit0Nor1Inv
			MAX-ACCESS read-write
			STATUS current
			DESCRIPTION
				"Phase applied to the secundary channel in the stereophonic audio pair for generating the monophonic audio in AES1R OUT"
		::= { ham3000c03v1Entry 167 }

		-- 1.3.6.1.4.1.10106.3.101291.1.1.169
		ham3000c03v1AesOut1rMono OBJECT-TYPE
			SYNTAX BitMask
			MAX-ACCESS read-write
			STATUS current
			DESCRIPTION
				"Monophonic audio generated from the audio pair assigned to AES1R OUT"
		::= { ham3000c03v1Entry 169 }

		-- 1.3.6.1.4.1.10106.3.101291.1.1.171
		ham3000c03v1AesOut2L OBJECT-TYPE
			SYNTAX AudioMxInputA
			MAX-ACCESS read-write
			STATUS current
			DESCRIPTION
				"Audio channel assignment to the digital audio output AES2L OUT"
		::= { ham3000c03v1Entry 171 }

		-- 1.3.6.1.4.1.10106.3.101291.1.1.173
		ham3000c03v1AesOut2lMonPh OBJECT-TYPE
			SYNTAX Bit0Nor1Inv
			MAX-ACCESS read-write
			STATUS current
			DESCRIPTION
				"Phase applied to the secundary channel in the stereophonic audio pair for generating the monophonic audio in AES2L OUT"
		::= { ham3000c03v1Entry 173 }

		-- 1.3.6.1.4.1.10106.3.101291.1.1.175
		ham3000c03v1AesOut2lMono OBJECT-TYPE
			SYNTAX BitMask
			MAX-ACCESS read-write
			STATUS current
			DESCRIPTION
				"Monophonic audio generated from the audio pair assigned to AES2L OUT"
		::= { ham3000c03v1Entry 175 }

		-- 1.3.6.1.4.1.10106.3.101291.1.1.177
		ham3000c03v1AesOut2R OBJECT-TYPE
			SYNTAX AudioMxInputA
			MAX-ACCESS read-write
			STATUS current
			DESCRIPTION
				"Audio channel assignment to the digital audio output AES2R OUT"
		::= { ham3000c03v1Entry 177 }

		-- 1.3.6.1.4.1.10106.3.101291.1.1.179
		ham3000c03v1AesOut2rMonPh OBJECT-TYPE
			SYNTAX Bit0Nor1Inv
			MAX-ACCESS read-write
			STATUS current
			DESCRIPTION
				"Phase applied to the secundary channel in the stereophonic audio pair for generating the monophonic audio in AES2R OUT"
		::= { ham3000c03v1Entry 179 }

		-- 1.3.6.1.4.1.10106.3.101291.1.1.181
		ham3000c03v1AesOut2rMono OBJECT-TYPE
			SYNTAX BitMask
			MAX-ACCESS read-write
			STATUS current
			DESCRIPTION
				"Monophonic audio generated from the audio pair assigned to AES2R OUT"
		::= { ham3000c03v1Entry 181 }

		-- 1.3.6.1.4.1.10106.3.101291.1.1.183
		ham3000c03v1AnalogOut1L OBJECT-TYPE
			SYNTAX AudioMxInputA
			MAX-ACCESS read-write
			STATUS current
			DESCRIPTION
				"Audio channel assignment to the analogue audio output ANALOG1L OUT"
		::= { ham3000c03v1Entry 183 }

		-- 1.3.6.1.4.1.10106.3.101291.1.1.185
		ham3000c03v1AnlOut1lMonPh OBJECT-TYPE
			SYNTAX Bit0Nor1Inv
			MAX-ACCESS read-write
			STATUS current
			DESCRIPTION
				"Phase applied to the secundary channel in the stereophonic audio pair for generating the monophonic audio in ANALOG1L OUT"
		::= { ham3000c03v1Entry 185 }

		-- 1.3.6.1.4.1.10106.3.101291.1.1.187
		ham3000c03v1AnlgOut1lMono OBJECT-TYPE
			SYNTAX BitMask
			MAX-ACCESS read-write
			STATUS current
			DESCRIPTION
				"Monophonic audio generated from the audio pair assigned to ANALOG1L OUT"
		::= { ham3000c03v1Entry 187 }

		-- 1.3.6.1.4.1.10106.3.101291.1.1.189
		ham3000c03v1AnalogOut1R OBJECT-TYPE
			SYNTAX AudioMxInputA
			MAX-ACCESS read-write
			STATUS current
			DESCRIPTION
				"Audio channel assignment to the analogue audio output ANALOG1R OUT"
		::= { ham3000c03v1Entry 189 }

		-- 1.3.6.1.4.1.10106.3.101291.1.1.191
		ham3000c03v1AnlOut1rMonPh OBJECT-TYPE
			SYNTAX Bit0Nor1Inv
			MAX-ACCESS read-write
			STATUS current
			DESCRIPTION
				"Phase applied to the secundary channel in the stereophonic audio pair for generating the monophonic audio in ANALOG1R OUT"
		::= { ham3000c03v1Entry 191 }

		-- 1.3.6.1.4.1.10106.3.101291.1.1.193
		ham3000c03v1AnlgOut1rMono OBJECT-TYPE
			SYNTAX BitMask
			MAX-ACCESS read-write
			STATUS current
			DESCRIPTION
				"Monophonic audio generated from the audio pair assigned to ANALOG1R OUT"
		::= { ham3000c03v1Entry 193 }

		-- 1.3.6.1.4.1.10106.3.101291.1.1.195
		ham3000c03v1AnalogOut2L OBJECT-TYPE
			SYNTAX AudioMxInputA
			MAX-ACCESS read-write
			STATUS current
			DESCRIPTION
				"Audio channel assignment to the analogue audio output ANALOG2L OUT"
		::= { ham3000c03v1Entry 195 }

		-- 1.3.6.1.4.1.10106.3.101291.1.1.197
		ham3000c03v1AnlOut2lMonPh OBJECT-TYPE
			SYNTAX Bit0Nor1Inv
			MAX-ACCESS read-write
			STATUS current
			DESCRIPTION
				"Phase applied to the secundary channel in the stereophonic audio pair for generating the monophonic audio in ANALOG2L OUT"
		::= { ham3000c03v1Entry 197 }

		-- 1.3.6.1.4.1.10106.3.101291.1.1.199
		ham3000c03v1AnlgOut2lMono OBJECT-TYPE
			SYNTAX BitMask
			MAX-ACCESS read-write
			STATUS current
			DESCRIPTION
				"Monophonic audio generated from the audio pair assigned to ANALOG2L OUT"
		::= { ham3000c03v1Entry 199 }

		-- 1.3.6.1.4.1.10106.3.101291.1.1.201
		ham3000c03v1AnalogOut2R OBJECT-TYPE
			SYNTAX AudioMxInputA
			MAX-ACCESS read-write
			STATUS current
			DESCRIPTION
				"Audio channel assignment to the analogue audio output ANALOG2R OUT"
		::= { ham3000c03v1Entry 201 }

		-- 1.3.6.1.4.1.10106.3.101291.1.1.203
		ham3000c03v1AnlOut2rMonPh OBJECT-TYPE
			SYNTAX Bit0Nor1Inv
			MAX-ACCESS read-write
			STATUS current
			DESCRIPTION
				"Phase applied to the secundary channel in the stereophonic audio pair for generating the monophonic audio in ANALOG2R OUT"
		::= { ham3000c03v1Entry 203 }

		-- 1.3.6.1.4.1.10106.3.101291.1.1.205
		ham3000c03v1AnlgOut2rMono OBJECT-TYPE
			SYNTAX BitMask
			MAX-ACCESS read-write
			STATUS current
			DESCRIPTION
				"Monophonic audio generated from the audio pair assigned to ANALOG2R OUT"
		::= { ham3000c03v1Entry 205 }

		-- 1.3.6.1.4.1.10106.3.101291.1.1.207
		ham3000c03v1GanG1p0l OBJECT-TYPE
			SYNTAX Gain24dbMute
			MAX-ACCESS read-write
			STATUS current
			DESCRIPTION
				"Gain applied to the digital audio channel embedded in G1P0L PGM OUT"
		::= { ham3000c03v1Entry 207 }

		-- 1.3.6.1.4.1.10106.3.101291.1.1.209
		ham3000c03v1PhaseG1p0l OBJECT-TYPE
			SYNTAX Bit0Nor1Inv
			MAX-ACCESS read-write
			STATUS current
			DESCRIPTION
				"Phase gain applied to the digital audio channel embedded in G1P0L PGM OUT"
		::= { ham3000c03v1Entry 209 }

		-- 1.3.6.1.4.1.10106.3.101291.1.1.211
		ham3000c03v1GanG1p0r OBJECT-TYPE
			SYNTAX Gain24dbMute
			MAX-ACCESS read-write
			STATUS current
			DESCRIPTION
				"Gain applied to the digital audio channel embedded in G1P0R PGM OUT"
		::= { ham3000c03v1Entry 211 }

		-- 1.3.6.1.4.1.10106.3.101291.1.1.213
		ham3000c03v1PhaseG1p0r OBJECT-TYPE
			SYNTAX Bit0Nor1Inv
			MAX-ACCESS read-write
			STATUS current
			DESCRIPTION
				"Phase gain applied to the digital audio channel embedded in G1P0R PGM OUT"
		::= { ham3000c03v1Entry 213 }

		-- 1.3.6.1.4.1.10106.3.101291.1.1.215
		ham3000c03v1GanG1p1l OBJECT-TYPE
			SYNTAX Gain24dbMute
			MAX-ACCESS read-write
			STATUS current
			DESCRIPTION
				"Gain applied to the digital audio channel embedded in G1P1L PGM OUT"
		::= { ham3000c03v1Entry 215 }

		-- 1.3.6.1.4.1.10106.3.101291.1.1.217
		ham3000c03v1PhaseG1p1l OBJECT-TYPE
			SYNTAX Bit0Nor1Inv
			MAX-ACCESS read-write
			STATUS current
			DESCRIPTION
				"Phase gain applied to the digital audio channel embedded in G1P1L PGM OUT"
		::= { ham3000c03v1Entry 217 }

		-- 1.3.6.1.4.1.10106.3.101291.1.1.219
		ham3000c03v1GanG1p1r OBJECT-TYPE
			SYNTAX Gain24dbMute
			MAX-ACCESS read-write
			STATUS current
			DESCRIPTION
				"Gain applied to the digital audio channel embedded in G1P1R PGM OUT"
		::= { ham3000c03v1Entry 219 }

		-- 1.3.6.1.4.1.10106.3.101291.1.1.221
		ham3000c03v1PhaseG1p1r OBJECT-TYPE
			SYNTAX Bit0Nor1Inv
			MAX-ACCESS read-write
			STATUS current
			DESCRIPTION
				"Phase gain applied to the digital audio channel embedded in G1P1R PGM OUT"
		::= { ham3000c03v1Entry 221 }

		-- 1.3.6.1.4.1.10106.3.101291.1.1.223
		ham3000c03v1GanG2p0l OBJECT-TYPE
			SYNTAX Gain24dbMute
			MAX-ACCESS read-write
			STATUS current
			DESCRIPTION
				"Gain applied to the digital audio channel embedded in G2P0L PGM OUT"
		::= { ham3000c03v1Entry 223 }

		-- 1.3.6.1.4.1.10106.3.101291.1.1.225
		ham3000c03v1PhaseG2p0l OBJECT-TYPE
			SYNTAX Bit0Nor1Inv
			MAX-ACCESS read-write
			STATUS current
			DESCRIPTION
				"Phase gain applied to the digital audio channel embedded in G2P0L PGM OUT"
		::= { ham3000c03v1Entry 225 }

		-- 1.3.6.1.4.1.10106.3.101291.1.1.227
		ham3000c03v1GanG2p0r OBJECT-TYPE
			SYNTAX Gain24dbMute
			MAX-ACCESS read-write
			STATUS current
			DESCRIPTION
				"Gain applied to the digital audio channel embedded in G2P0R PGM OUT"
		::= { ham3000c03v1Entry 227 }

		-- 1.3.6.1.4.1.10106.3.101291.1.1.229
		ham3000c03v1PhaseG2p0r OBJECT-TYPE
			SYNTAX Bit0Nor1Inv
			MAX-ACCESS read-write
			STATUS current
			DESCRIPTION
				"Phase gain applied to the digital audio channel embedded in G2P0R PGM OUT"
		::= { ham3000c03v1Entry 229 }

		-- 1.3.6.1.4.1.10106.3.101291.1.1.231
		ham3000c03v1GanG2p1l OBJECT-TYPE
			SYNTAX Gain24dbMute
			MAX-ACCESS read-write
			STATUS current
			DESCRIPTION
				"Gain applied to the digital audio channel embedded in G2P1L PGM OUT"
		::= { ham3000c03v1Entry 231 }

		-- 1.3.6.1.4.1.10106.3.101291.1.1.233
		ham3000c03v1PhaseG2p1l OBJECT-TYPE
			SYNTAX Bit0Nor1Inv
			MAX-ACCESS read-write
			STATUS current
			DESCRIPTION
				"Phase gain applied to the digital audio channel embedded in G2P1L PGM OUT"
		::= { ham3000c03v1Entry 233 }

		-- 1.3.6.1.4.1.10106.3.101291.1.1.235
		ham3000c03v1GanG2p1r OBJECT-TYPE
			SYNTAX Gain24dbMute
			MAX-ACCESS read-write
			STATUS current
			DESCRIPTION
				"Gain applied to the digital audio channel embedded in G2P1R PGM OUT"
		::= { ham3000c03v1Entry 235 }

		-- 1.3.6.1.4.1.10106.3.101291.1.1.237
		ham3000c03v1PhaseG2p1r OBJECT-TYPE
			SYNTAX Bit0Nor1Inv
			MAX-ACCESS read-write
			STATUS current
			DESCRIPTION
				"Phase gain applied to the digital audio channel embedded in G2P1R PGM OUT"
		::= { ham3000c03v1Entry 237 }

		-- 1.3.6.1.4.1.10106.3.101291.1.1.239
		ham3000c03v1GanG3p0l OBJECT-TYPE
			SYNTAX Gain24dbMute
			MAX-ACCESS read-write
			STATUS current
			DESCRIPTION
				"Gain applied to the digital audio channel embedded in G3P0L PGM OUT"
		::= { ham3000c03v1Entry 239 }

		-- 1.3.6.1.4.1.10106.3.101291.1.1.241
		ham3000c03v1PhaseG3p0l OBJECT-TYPE
			SYNTAX Bit0Nor1Inv
			MAX-ACCESS read-write
			STATUS current
			DESCRIPTION
				"Phase gain applied to the digital audio channel embedded in G3P0L PGM OUT"
		::= { ham3000c03v1Entry 241 }

		-- 1.3.6.1.4.1.10106.3.101291.1.1.243
		ham3000c03v1GanG3p0r OBJECT-TYPE
			SYNTAX Gain24dbMute
			MAX-ACCESS read-write
			STATUS current
			DESCRIPTION
				"Gain applied to the digital audio channel embedded in G3P0R PGM OUT"
		::= { ham3000c03v1Entry 243 }

		-- 1.3.6.1.4.1.10106.3.101291.1.1.245
		ham3000c03v1PhaseG3p0r OBJECT-TYPE
			SYNTAX Bit0Nor1Inv
			MAX-ACCESS read-write
			STATUS current
			DESCRIPTION
				"Phase gain applied to the digital audio channel embedded in G3P0R PGM OUT"
		::= { ham3000c03v1Entry 245 }

		-- 1.3.6.1.4.1.10106.3.101291.1.1.247
		ham3000c03v1GanG3p1l OBJECT-TYPE
			SYNTAX Gain24dbMute
			MAX-ACCESS read-write
			STATUS current
			DESCRIPTION
				"Gain applied to the digital audio channel embedded in G3P1L PGM OUT"
		::= { ham3000c03v1Entry 247 }

		-- 1.3.6.1.4.1.10106.3.101291.1.1.249
		ham3000c03v1PhaseG3p1l OBJECT-TYPE
			SYNTAX Bit0Nor1Inv
			MAX-ACCESS read-write
			STATUS current
			DESCRIPTION
				"Phase gain applied to the digital audio channel embedded in G3P1L PGM OUT"
		::= { ham3000c03v1Entry 249 }

		-- 1.3.6.1.4.1.10106.3.101291.1.1.251
		ham3000c03v1GanG3p1r OBJECT-TYPE
			SYNTAX Gain24dbMute
			MAX-ACCESS read-write
			STATUS current
			DESCRIPTION
				"Gain applied to the digital audio channel embedded in G3P1R PGM OUT"
		::= { ham3000c03v1Entry 251 }

		-- 1.3.6.1.4.1.10106.3.101291.1.1.253
		ham3000c03v1PhaseG3p1r OBJECT-TYPE
			SYNTAX Bit0Nor1Inv
			MAX-ACCESS read-write
			STATUS current
			DESCRIPTION
				"Phase gain applied to the digital audio channel embedded in G3P1R PGM OUT"
		::= { ham3000c03v1Entry 253 }

		-- 1.3.6.1.4.1.10106.3.101291.1.1.255
		ham3000c03v1GanG4p0l OBJECT-TYPE
			SYNTAX Gain24dbMute
			MAX-ACCESS read-write
			STATUS current
			DESCRIPTION
				"Gain applied to the digital audio channel embedded in G4P0L PGM OUT"
		::= { ham3000c03v1Entry 255 }

		-- 1.3.6.1.4.1.10106.3.101291.1.1.257
		ham3000c03v1PhaseG4p0l OBJECT-TYPE
			SYNTAX Bit0Nor1Inv
			MAX-ACCESS read-write
			STATUS current
			DESCRIPTION
				"Phase gain applied to the digital audio channel embedded in G4P0L PGM OUT"
		::= { ham3000c03v1Entry 257 }

		-- 1.3.6.1.4.1.10106.3.101291.1.1.259
		ham3000c03v1GanG4p0r OBJECT-TYPE
			SYNTAX Gain24dbMute
			MAX-ACCESS read-write
			STATUS current
			DESCRIPTION
				"Gain applied to the digital audio channel embedded in G4P0R PGM OUT"
		::= { ham3000c03v1Entry 259 }

		-- 1.3.6.1.4.1.10106.3.101291.1.1.261
		ham3000c03v1PhaseG4p0r OBJECT-TYPE
			SYNTAX Bit0Nor1Inv
			MAX-ACCESS read-write
			STATUS current
			DESCRIPTION
				"Phase gain applied to the digital audio channel embedded in G4P0R PGM OUT"
		::= { ham3000c03v1Entry 261 }

		-- 1.3.6.1.4.1.10106.3.101291.1.1.263
		ham3000c03v1GanG4p1l OBJECT-TYPE
			SYNTAX Gain24dbMute
			MAX-ACCESS read-write
			STATUS current
			DESCRIPTION
				"Gain applied to the digital audio channel embedded in G4P1L PGM OUT"
		::= { ham3000c03v1Entry 263 }

		-- 1.3.6.1.4.1.10106.3.101291.1.1.265
		ham3000c03v1PhaseG4p1l OBJECT-TYPE
			SYNTAX Bit0Nor1Inv
			MAX-ACCESS read-write
			STATUS current
			DESCRIPTION
				"Phase gain applied to the digital audio channel embedded in G4P1L PGM OUT"
		::= { ham3000c03v1Entry 265 }

		-- 1.3.6.1.4.1.10106.3.101291.1.1.267
		ham3000c03v1GanG4p1r OBJECT-TYPE
			SYNTAX Gain24dbMute
			MAX-ACCESS read-write
			STATUS current
			DESCRIPTION
				"Gain applied to the digital audio channel embedded in G4P1R PGM OUT"
		::= { ham3000c03v1Entry 267 }

		-- 1.3.6.1.4.1.10106.3.101291.1.1.269
		ham3000c03v1PhaseG4p1r OBJECT-TYPE
			SYNTAX Bit0Nor1Inv
			MAX-ACCESS read-write
			STATUS current
			DESCRIPTION
				"Phase gain applied to the digital audio channel embedded in G4P1R PGM OUT"
		::= { ham3000c03v1Entry 269 }

		-- 1.3.6.1.4.1.10106.3.101291.1.1.271
		ham3000c03v1GanAes1l OBJECT-TYPE
			SYNTAX Gain24dbMute
			MAX-ACCESS read-write
			STATUS current
			DESCRIPTION
				"Gain applied to the digital audio channel output AES1L OUT"
		::= { ham3000c03v1Entry 271 }

		-- 1.3.6.1.4.1.10106.3.101291.1.1.273
		ham3000c03v1PhaseAes1l OBJECT-TYPE
			SYNTAX Bit0Nor1Inv
			MAX-ACCESS read-write
			STATUS current
			DESCRIPTION
				"Phase gain applied to the digital audio channel output AES1L OUT"
		::= { ham3000c03v1Entry 273 }

		-- 1.3.6.1.4.1.10106.3.101291.1.1.275
		ham3000c03v1GanAes1r OBJECT-TYPE
			SYNTAX Gain24dbMute
			MAX-ACCESS read-write
			STATUS current
			DESCRIPTION
				"Gain applied to the digital audio channel output AES1R OUT"
		::= { ham3000c03v1Entry 275 }

		-- 1.3.6.1.4.1.10106.3.101291.1.1.277
		ham3000c03v1PhaseAes1r OBJECT-TYPE
			SYNTAX Bit0Nor1Inv
			MAX-ACCESS read-write
			STATUS current
			DESCRIPTION
				"Phase gain applied to the digital audio channel output AES1R OUT"
		::= { ham3000c03v1Entry 277 }

		-- 1.3.6.1.4.1.10106.3.101291.1.1.279
		ham3000c03v1GanAes2l OBJECT-TYPE
			SYNTAX Gain24dbMute
			MAX-ACCESS read-write
			STATUS current
			DESCRIPTION
				"Gain applied to the digital audio channel output AES2L OUT"
		::= { ham3000c03v1Entry 279 }

		-- 1.3.6.1.4.1.10106.3.101291.1.1.281
		ham3000c03v1PhaseAes2l OBJECT-TYPE
			SYNTAX Bit0Nor1Inv
			MAX-ACCESS read-write
			STATUS current
			DESCRIPTION
				"Phase gain applied to the digital audio channel output AES2L OUT"
		::= { ham3000c03v1Entry 281 }

		-- 1.3.6.1.4.1.10106.3.101291.1.1.283
		ham3000c03v1GanAes2r OBJECT-TYPE
			SYNTAX Gain24dbMute
			MAX-ACCESS read-write
			STATUS current
			DESCRIPTION
				"Gain applied to the digital audio channel output AES2R OUT"
		::= { ham3000c03v1Entry 283 }

		-- 1.3.6.1.4.1.10106.3.101291.1.1.285
		ham3000c03v1PhaseAes2r OBJECT-TYPE
			SYNTAX Bit0Nor1Inv
			MAX-ACCESS read-write
			STATUS current
			DESCRIPTION
				"Phase gain applied to the digital audio channel output AES2R OUT"
		::= { ham3000c03v1Entry 285 }

		-- 1.3.6.1.4.1.10106.3.101291.1.1.287
		ham3000c03v1GanAnlg1l OBJECT-TYPE
			SYNTAX Gain24dbMute
			MAX-ACCESS read-write
			STATUS current
			DESCRIPTION
				"Gain applied to the analogue audio channel output ANALOG1L OUT"
		::= { ham3000c03v1Entry 287 }

		-- 1.3.6.1.4.1.10106.3.101291.1.1.289
		ham3000c03v1PhaseAnlg1l OBJECT-TYPE
			SYNTAX Bit0Nor1Inv
			MAX-ACCESS read-write
			STATUS current
			DESCRIPTION
				"Phase gain applied to the analogue audio channel output ANALOG1L OUT"
		::= { ham3000c03v1Entry 289 }

		-- 1.3.6.1.4.1.10106.3.101291.1.1.291
		ham3000c03v1GanAnlg1r OBJECT-TYPE
			SYNTAX Gain24dbMute
			MAX-ACCESS read-write
			STATUS current
			DESCRIPTION
				"Gain applied to the analogue audio channel output ANALOG1R OUT"
		::= { ham3000c03v1Entry 291 }

		-- 1.3.6.1.4.1.10106.3.101291.1.1.293
		ham3000c03v1PhaseAnlg1r OBJECT-TYPE
			SYNTAX Bit0Nor1Inv
			MAX-ACCESS read-write
			STATUS current
			DESCRIPTION
				"Phase gain applied to the analogue audio channel output ANALOG1R OUT"
		::= { ham3000c03v1Entry 293 }

		-- 1.3.6.1.4.1.10106.3.101291.1.1.295
		ham3000c03v1GanAnlg2l OBJECT-TYPE
			SYNTAX Gain24dbMute
			MAX-ACCESS read-write
			STATUS current
			DESCRIPTION
				"Gain applied to the analogue audio channel output ANALOG2L OUT"
		::= { ham3000c03v1Entry 295 }

		-- 1.3.6.1.4.1.10106.3.101291.1.1.297
		ham3000c03v1PhaseAnlg2l OBJECT-TYPE
			SYNTAX Bit0Nor1Inv
			MAX-ACCESS read-write
			STATUS current
			DESCRIPTION
				"Phase gain applied to the analogue audio channel output ANALOG2L OUT"
		::= { ham3000c03v1Entry 297 }

		-- 1.3.6.1.4.1.10106.3.101291.1.1.299
		ham3000c03v1GanAnlg2r OBJECT-TYPE
			SYNTAX Gain24dbMute
			MAX-ACCESS read-write
			STATUS current
			DESCRIPTION
				"Gain applied to the analogue audio channel output ANALOG2R OUT"
		::= { ham3000c03v1Entry 299 }

		-- 1.3.6.1.4.1.10106.3.101291.1.1.301
		ham3000c03v1PhaseAnlg2r OBJECT-TYPE
			SYNTAX Bit0Nor1Inv
			MAX-ACCESS read-write
			STATUS current
			DESCRIPTION
				"Phase gain applied to the analogue audio channel output ANALOG2R OUT"
		::= { ham3000c03v1Entry 301 }

		-- 1.3.6.1.4.1.10106.3.101291.1.1.303
		ham3000c03v1DelayG1p0l OBJECT-TYPE
			SYNTAX DelayAud
			MAX-ACCESS read-write
			STATUS current
			DESCRIPTION
				"Audio delay in the audio channel embedded in G1P0L PGM OUT"
		::= { ham3000c03v1Entry 303 }

		-- 1.3.6.1.4.1.10106.3.101291.1.1.305
		ham3000c03v1DelayG1p0r OBJECT-TYPE
			SYNTAX DelayAud
			MAX-ACCESS read-write
			STATUS current
			DESCRIPTION
				"Audio delay in the audio channel embedded in G1P0R PGM OUT"
		::= { ham3000c03v1Entry 305 }

		-- 1.3.6.1.4.1.10106.3.101291.1.1.307
		ham3000c03v1DelayG1p1l OBJECT-TYPE
			SYNTAX DelayAud
			MAX-ACCESS read-write
			STATUS current
			DESCRIPTION
				"Audio delay in the audio channel embedded in G1P1L PGM OUT"
		::= { ham3000c03v1Entry 307 }

		-- 1.3.6.1.4.1.10106.3.101291.1.1.309
		ham3000c03v1DelayG1p1r OBJECT-TYPE
			SYNTAX DelayAud
			MAX-ACCESS read-write
			STATUS current
			DESCRIPTION
				"Audio delay in the audio channel embedded in G1P1R PGM OUT"
		::= { ham3000c03v1Entry 309 }

		-- 1.3.6.1.4.1.10106.3.101291.1.1.311
		ham3000c03v1DelayG2p0l OBJECT-TYPE
			SYNTAX DelayAud
			MAX-ACCESS read-write
			STATUS current
			DESCRIPTION
				"Audio delay in the audio channel embedded in G2P0L PGM OUT"
		::= { ham3000c03v1Entry 311 }

		-- 1.3.6.1.4.1.10106.3.101291.1.1.313
		ham3000c03v1DelayG2p0r OBJECT-TYPE
			SYNTAX DelayAud
			MAX-ACCESS read-write
			STATUS current
			DESCRIPTION
				"Audio delay in the audio channel embedded in G2P1R PGM OUT"
		::= { ham3000c03v1Entry 313 }

		-- 1.3.6.1.4.1.10106.3.101291.1.1.315
		ham3000c03v1DelayG2p1l OBJECT-TYPE
			SYNTAX DelayAud
			MAX-ACCESS read-write
			STATUS current
			DESCRIPTION
				"Audio delay in the audio channel embedded in G2P1L PGM OUT"
		::= { ham3000c03v1Entry 315 }

		-- 1.3.6.1.4.1.10106.3.101291.1.1.317
		ham3000c03v1DelayG2p1r OBJECT-TYPE
			SYNTAX DelayAud
			MAX-ACCESS read-write
			STATUS current
			DESCRIPTION
				"Audio delay in the audio channel embedded in G2P1R PGM OUT"
		::= { ham3000c03v1Entry 317 }

		-- 1.3.6.1.4.1.10106.3.101291.1.1.319
		ham3000c03v1DelayG3p0l OBJECT-TYPE
			SYNTAX DelayAud
			MAX-ACCESS read-write
			STATUS current
			DESCRIPTION
				"Audio delay in the audio channel embedded in G3P0L PGM OUT"
		::= { ham3000c03v1Entry 319 }

		-- 1.3.6.1.4.1.10106.3.101291.1.1.321
		ham3000c03v1DelayG3p0r OBJECT-TYPE
			SYNTAX DelayAud
			MAX-ACCESS read-write
			STATUS current
			DESCRIPTION
				"Audio delay in the audio channel embedded in G3P0R PGM OUT"
		::= { ham3000c03v1Entry 321 }

		-- 1.3.6.1.4.1.10106.3.101291.1.1.323
		ham3000c03v1DelayG3p1l OBJECT-TYPE
			SYNTAX DelayAud
			MAX-ACCESS read-write
			STATUS current
			DESCRIPTION
				"Audio delay in the audio channel embedded in G3P1L PGM OUT"
		::= { ham3000c03v1Entry 323 }

		-- 1.3.6.1.4.1.10106.3.101291.1.1.325
		ham3000c03v1DelayG3p1r OBJECT-TYPE
			SYNTAX DelayAud
			MAX-ACCESS read-write
			STATUS current
			DESCRIPTION
				"Audio delay in the audio channel embedded in G3P1R PGM OUT"
		::= { ham3000c03v1Entry 325 }

		-- 1.3.6.1.4.1.10106.3.101291.1.1.327
		ham3000c03v1DelayG4p0l OBJECT-TYPE
			SYNTAX DelayAud
			MAX-ACCESS read-write
			STATUS current
			DESCRIPTION
				"Audio delay in the audio channel embedded in G4P0L PGM OUT"
		::= { ham3000c03v1Entry 327 }

		-- 1.3.6.1.4.1.10106.3.101291.1.1.329
		ham3000c03v1DelayG4p0r OBJECT-TYPE
			SYNTAX DelayAud
			MAX-ACCESS read-write
			STATUS current
			DESCRIPTION
				"Audio delay in the audio channel embedded in G4P0R PGM OUT"
		::= { ham3000c03v1Entry 329 }

		-- 1.3.6.1.4.1.10106.3.101291.1.1.331
		ham3000c03v1DelayG4p1l OBJECT-TYPE
			SYNTAX DelayAud
			MAX-ACCESS read-write
			STATUS current
			DESCRIPTION
				"Audio delay in the audio channel embedded in G4P1L PGM OUT"
		::= { ham3000c03v1Entry 331 }

		-- 1.3.6.1.4.1.10106.3.101291.1.1.333
		ham3000c03v1DelayG4p1r OBJECT-TYPE
			SYNTAX DelayAud
			MAX-ACCESS read-write
			STATUS current
			DESCRIPTION
				"Audio delay in the audio channel embedded in G4P1R PGM OUT"
		::= { ham3000c03v1Entry 333 }

		-- 1.3.6.1.4.1.10106.3.101291.1.1.335
		ham3000c03v1DelayAes1l OBJECT-TYPE
			SYNTAX DelayAud
			MAX-ACCESS read-write
			STATUS current
			DESCRIPTION
				"Audio delay in the digital audio channel AES1L OUT"
		::= { ham3000c03v1Entry 335 }

		-- 1.3.6.1.4.1.10106.3.101291.1.1.337
		ham3000c03v1DelayAes1r OBJECT-TYPE
			SYNTAX DelayAud
			MAX-ACCESS read-write
			STATUS current
			DESCRIPTION
				"Audio delay in the digital audio channel AES1R OUT"
		::= { ham3000c03v1Entry 337 }

		-- 1.3.6.1.4.1.10106.3.101291.1.1.339
		ham3000c03v1DelayAes2l OBJECT-TYPE
			SYNTAX DelayAud
			MAX-ACCESS read-write
			STATUS current
			DESCRIPTION
				"Audio delay in the digital audio channel AES2L OUT"
		::= { ham3000c03v1Entry 339 }

		-- 1.3.6.1.4.1.10106.3.101291.1.1.341
		ham3000c03v1DelayAes2r OBJECT-TYPE
			SYNTAX DelayAud
			MAX-ACCESS read-write
			STATUS current
			DESCRIPTION
				"Audio delay in the digital audio channel AES2R OUT"
		::= { ham3000c03v1Entry 341 }

		-- 1.3.6.1.4.1.10106.3.101291.1.1.343
		ham3000c03v1DelayAnlg1l OBJECT-TYPE
			SYNTAX DelayAud
			MAX-ACCESS read-write
			STATUS current
			DESCRIPTION
				"Audio delay in the analogue audio channel ANALOG1L OUT"
		::= { ham3000c03v1Entry 343 }

		-- 1.3.6.1.4.1.10106.3.101291.1.1.345
		ham3000c03v1DelayAnlg1r OBJECT-TYPE
			SYNTAX DelayAud
			MAX-ACCESS read-write
			STATUS current
			DESCRIPTION
				"Audio delay in the analogue audio channel ANALOG1R OUT"
		::= { ham3000c03v1Entry 345 }

		-- 1.3.6.1.4.1.10106.3.101291.1.1.347
		ham3000c03v1DelayAnlg2l OBJECT-TYPE
			SYNTAX DelayAud
			MAX-ACCESS read-write
			STATUS current
			DESCRIPTION
				"Audio delay in the analogue audio channel ANALOG2L OUT"
		::= { ham3000c03v1Entry 347 }

		-- 1.3.6.1.4.1.10106.3.101291.1.1.349
		ham3000c03v1DelayAnlg2r OBJECT-TYPE
			SYNTAX DelayAud
			MAX-ACCESS read-write
			STATUS current
			DESCRIPTION
				"Audio delay in the analogue audio channel ANALOG2R OUT"
		::= { ham3000c03v1Entry 349 }

		-- 1.3.6.1.4.1.10106.3.101291.1.1.351
		ham3000c03v1StatFlash OBJECT-TYPE
			SYNTAX BitFailN
			MAX-ACCESS read-only
			STATUS current
			DESCRIPTION
				"Displays the Flash state"
		::= { ham3000c03v1Entry 351 }

		-- 1.3.6.1.4.1.10106.3.101291.1.1.353
		ham3000c03v1NoSignalMain OBJECT-TYPE
			SYNTAX BitFail
			MAX-ACCESS read-only
			STATUS current
			DESCRIPTION
				"There is no SDI signal or the format is not supported in PGM IN"
		::= { ham3000c03v1Entry 353 }

		-- 1.3.6.1.4.1.10106.3.101291.1.1.354
		ham3000c03v1NoSignalMainTrapEnable OBJECT-TYPE
			SYNTAX AlarmEnable
			MAX-ACCESS read-write
			STATUS current
			DESCRIPTION
				"There is no SDI signal or the format is not supported in PGM IN Trap Enable"
		::= { ham3000c03v1Entry 354 }

		-- 1.3.6.1.4.1.10106.3.101291.1.1.355
		ham3000c03v1UnlockMain OBJECT-TYPE
			SYNTAX BitFail
			MAX-ACCESS read-only
			STATUS current
			DESCRIPTION
				"Indicates signal unlock fail"
		::= { ham3000c03v1Entry 355 }

		-- 1.3.6.1.4.1.10106.3.101291.1.1.356
		ham3000c03v1UnlockMainTrapEnable OBJECT-TYPE
			SYNTAX AlarmEnable
			MAX-ACCESS read-write
			STATUS current
			DESCRIPTION
				"Indicates signal unlock fail Trap Enable"
		::= { ham3000c03v1Entry 356 }

		-- 1.3.6.1.4.1.10106.3.101291.1.1.357
		ham3000c03v1EdhErrorMain OBJECT-TYPE
			SYNTAX BitFail
			MAX-ACCESS read-only
			STATUS current
			DESCRIPTION
				"There are EDH/CRC errors on PGM IN"
		::= { ham3000c03v1Entry 357 }

		-- 1.3.6.1.4.1.10106.3.101291.1.1.358
		ham3000c03v1EdhErrorMainTrapEnable OBJECT-TYPE
			SYNTAX AlarmEnable
			MAX-ACCESS read-write
			STATUS current
			DESCRIPTION
				"There are EDH/CRC errors on PGM IN Trap Enable"
		::= { ham3000c03v1Entry 358 }

		-- 1.3.6.1.4.1.10106.3.101291.1.1.359
		ham3000c03v1NoSignalAux OBJECT-TYPE
			SYNTAX BitFail
			MAX-ACCESS read-only
			STATUS current
			DESCRIPTION
				"There is no SDI signal or the format is not supported in AUX IN"
		::= { ham3000c03v1Entry 359 }

		-- 1.3.6.1.4.1.10106.3.101291.1.1.361
		ham3000c03v1UnlockAux OBJECT-TYPE
			SYNTAX BitFail
			MAX-ACCESS read-only
			STATUS current
			DESCRIPTION
				"Indicates signal AUX IN unlock fail"
		::= { ham3000c03v1Entry 361 }

		-- 1.3.6.1.4.1.10106.3.101291.1.1.363
		ham3000c03v1EdhErrorAux OBJECT-TYPE
			SYNTAX BitFail
			MAX-ACCESS read-only
			STATUS current
			DESCRIPTION
				"There are EDH/CRC errors on AUX IN signal"
		::= { ham3000c03v1Entry 363 }

		-- 1.3.6.1.4.1.10106.3.101291.1.1.365
		ham3000c03v1RefAbsent OBJECT-TYPE
			SYNTAX BitFail
			MAX-ACCESS read-only
			STATUS current
			DESCRIPTION
				"There is no reference signal"
		::= { ham3000c03v1Entry 365 }

		-- 1.3.6.1.4.1.10106.3.101291.1.1.366
		ham3000c03v1RefAbsentTrapEnable OBJECT-TYPE
			SYNTAX AlarmEnable
			MAX-ACCESS read-write
			STATUS current
			DESCRIPTION
				"There is no reference signal Trap Enable"
		::= { ham3000c03v1Entry 366 }

		-- 1.3.6.1.4.1.10106.3.101291.1.1.367
		ham3000c03v1RefUnlock OBJECT-TYPE
			SYNTAX BitFail
			MAX-ACCESS read-only
			STATUS current
			DESCRIPTION
				"Reference input unlock fail"
		::= { ham3000c03v1Entry 367 }

		-- 1.3.6.1.4.1.10106.3.101291.1.1.368
		ham3000c03v1RefUnlockTrapEnable OBJECT-TYPE
			SYNTAX AlarmEnable
			MAX-ACCESS read-write
			STATUS current
			DESCRIPTION
				"Reference input unlock fail Trap Enable"
		::= { ham3000c03v1Entry 368 }

		-- 1.3.6.1.4.1.10106.3.101291.1.1.369
		ham3000c03v1FormatMainIn OBJECT-TYPE
			SYNTAX SdiHd3gFmt3
			MAX-ACCESS read-only
			STATUS current
			DESCRIPTION
				"Indicates the SDI received signal format"
		::= { ham3000c03v1Entry 369 }

		-- 1.3.6.1.4.1.10106.3.101291.1.1.371
		ham3000c03v1FormatAuxIn OBJECT-TYPE
			SYNTAX SdiHd3gFmt3
			MAX-ACCESS read-only
			STATUS current
			DESCRIPTION
				"Indicates the SDI_AUX received signal format"
		::= { ham3000c03v1Entry 371 }

		-- 1.3.6.1.4.1.10106.3.101291.1.1.373
		ham3000c03v1FormatRef OBJECT-TYPE
			SYNTAX SdiHd3gFmt3
			MAX-ACCESS read-only
			STATUS current
			DESCRIPTION
				"Indicates the input reference signal format"
		::= { ham3000c03v1Entry 373 }

		-- 1.3.6.1.4.1.10106.3.101291.1.1.375
		ham3000c03v1FormatMainTx OBJECT-TYPE
			SYNTAX SdiHd3gFmt3
			MAX-ACCESS read-only
			STATUS current
			DESCRIPTION
				"Indicates the SDI transmited signal format"
		::= { ham3000c03v1Entry 375 }

		-- 1.3.6.1.4.1.10106.3.101291.1.1.377
		ham3000c03v1SigDelay OBJECT-TYPE
			SYNTAX DelayX20Us
			MAX-ACCESS read-only
			STATUS current
			DESCRIPTION
				"Indicates the input to output delay"
		::= { ham3000c03v1Entry 377 }

		-- 1.3.6.1.4.1.10106.3.101291.1.1.379
		ham3000c03v1Gr1MainPres OBJECT-TYPE
			SYNTAX Bit0No1Yes
			MAX-ACCESS read-only
			STATUS current
			DESCRIPTION
				"Indicates group 1 presence in PGM IN"
		::= { ham3000c03v1Entry 379 }

		-- 1.3.6.1.4.1.10106.3.101291.1.1.380
		ham3000c03v1Gr1MainPresTrapEnable OBJECT-TYPE
			SYNTAX AlarmEnable
			MAX-ACCESS read-write
			STATUS current
			DESCRIPTION
				"Indicates group 1 presence in PGM IN Trap Enable"
		::= { ham3000c03v1Entry 380 }

		-- 1.3.6.1.4.1.10106.3.101291.1.1.381
		ham3000c03v1Gr2MainPres OBJECT-TYPE
			SYNTAX Bit0No1Yes
			MAX-ACCESS read-only
			STATUS current
			DESCRIPTION
				"Indicates group 2 presence in PGM IN"
		::= { ham3000c03v1Entry 381 }

		-- 1.3.6.1.4.1.10106.3.101291.1.1.382
		ham3000c03v1Gr2MainPresTrapEnable OBJECT-TYPE
			SYNTAX AlarmEnable
			MAX-ACCESS read-write
			STATUS current
			DESCRIPTION
				"Indicates group 2 presence in PGM IN Trap Enable"
		::= { ham3000c03v1Entry 382 }

		-- 1.3.6.1.4.1.10106.3.101291.1.1.383
		ham3000c03v1Gr3MainPres OBJECT-TYPE
			SYNTAX Bit0No1Yes
			MAX-ACCESS read-only
			STATUS current
			DESCRIPTION
				"Indicates group 3 presence in PGM IN"
		::= { ham3000c03v1Entry 383 }

		-- 1.3.6.1.4.1.10106.3.101291.1.1.384
		ham3000c03v1Gr3MainPresTrapEnable OBJECT-TYPE
			SYNTAX AlarmEnable
			MAX-ACCESS read-write
			STATUS current
			DESCRIPTION
				"Indicates group 3 presence in PGM IN Trap Enable"
		::= { ham3000c03v1Entry 384 }

		-- 1.3.6.1.4.1.10106.3.101291.1.1.385
		ham3000c03v1Gr4MainPres OBJECT-TYPE
			SYNTAX Bit0No1Yes
			MAX-ACCESS read-only
			STATUS current
			DESCRIPTION
				"Indicates group 4 presence in PGM IN"
		::= { ham3000c03v1Entry 385 }

		-- 1.3.6.1.4.1.10106.3.101291.1.1.386
		ham3000c03v1Gr4MainPresTrapEnable OBJECT-TYPE
			SYNTAX AlarmEnable
			MAX-ACCESS read-write
			STATUS current
			DESCRIPTION
				"Indicates group 4 presence in PGM IN Trap Enable"
		::= { ham3000c03v1Entry 386 }

		-- 1.3.6.1.4.1.10106.3.101291.1.1.387
		ham3000c03v1Gr1AuxPres OBJECT-TYPE
			SYNTAX Bit0No1Yes
			MAX-ACCESS read-only
			STATUS current
			DESCRIPTION
				"Indicates group 1 presence in AUX IN"
		::= { ham3000c03v1Entry 387 }

		-- 1.3.6.1.4.1.10106.3.101291.1.1.389
		ham3000c03v1Gr2AuxPres OBJECT-TYPE
			SYNTAX Bit0No1Yes
			MAX-ACCESS read-only
			STATUS current
			DESCRIPTION
				"Indicates group 2 presence in AUX IN"
		::= { ham3000c03v1Entry 389 }

		-- 1.3.6.1.4.1.10106.3.101291.1.1.391
		ham3000c03v1Gr3AuxPres OBJECT-TYPE
			SYNTAX Bit0No1Yes
			MAX-ACCESS read-only
			STATUS current
			DESCRIPTION
				"Indicates group 3 presence in AUX IN"
		::= { ham3000c03v1Entry 391 }

		-- 1.3.6.1.4.1.10106.3.101291.1.1.393
		ham3000c03v1Gr4AuxPres OBJECT-TYPE
			SYNTAX Bit0No1Yes
			MAX-ACCESS read-only
			STATUS current
			DESCRIPTION
				"Indicates group 4 presence in AUX IN"
		::= { ham3000c03v1Entry 393 }

		-- 1.3.6.1.4.1.10106.3.101291.1.1.395
		ham3000c03v1Aes1Ok OBJECT-TYPE
			SYNTAX BitFailN
			MAX-ACCESS read-only
			STATUS current
			DESCRIPTION
				"Indicates frame validity of input AES1"
		::= { ham3000c03v1Entry 395 }

		-- 1.3.6.1.4.1.10106.3.101291.1.1.397
		ham3000c03v1Aes1Frq OBJECT-TYPE
			SYNTAX AudioSelFreq6
			MAX-ACCESS read-only
			STATUS current
			DESCRIPTION
				"Indicates sampling frequency of the AES1 input"
		::= { ham3000c03v1Entry 397 }

		-- 1.3.6.1.4.1.10106.3.101291.1.1.399
		ham3000c03v1Aes2Ok OBJECT-TYPE
			SYNTAX BitFailN
			MAX-ACCESS read-only
			STATUS current
			DESCRIPTION
				"Indicates frame validity of input AES2"
		::= { ham3000c03v1Entry 399 }

		-- 1.3.6.1.4.1.10106.3.101291.1.1.401
		ham3000c03v1Aes2Frq OBJECT-TYPE
			SYNTAX AudioSelFreq6
			MAX-ACCESS read-only
			STATUS current
			DESCRIPTION
				"Indicates sampling frequency of the AES2 input"
		::= { ham3000c03v1Entry 401 }

		-- 1.3.6.1.4.1.10106.3.101291.1.1.403
		ham3000c03v1AudStatMain OBJECT-TYPE
			SYNTAX BitFail
			MAX-ACCESS read-only
			STATUS current
			DESCRIPTION
				"Indicates audio fail in audio channels embedded in PGM IN"
		::= { ham3000c03v1Entry 403 }

		-- 1.3.6.1.4.1.10106.3.101291.1.1.404
		ham3000c03v1AudStatMainTrapEnable OBJECT-TYPE
			SYNTAX AlarmEnable
			MAX-ACCESS read-write
			STATUS current
			DESCRIPTION
				"Indicates audio fail in audio channels embedded in PGM IN Trap Enable"
		::= { ham3000c03v1Entry 404 }

		-- 1.3.6.1.4.1.10106.3.101291.1.1.405
		ham3000c03v1AudStatAux OBJECT-TYPE
			SYNTAX BitFail
			MAX-ACCESS read-only
			STATUS current
			DESCRIPTION
				"Indicates audio fail in audio channels embedded in AUX IN"
		::= { ham3000c03v1Entry 405 }

		-- 1.3.6.1.4.1.10106.3.101291.1.1.406
		ham3000c03v1AudStatAuxTrapEnable OBJECT-TYPE
			SYNTAX AlarmEnable
			MAX-ACCESS read-write
			STATUS current
			DESCRIPTION
				"Indicates audio fail in audio channels embedded in AUX IN Trap Enable"
		::= { ham3000c03v1Entry 406 }

		-- 1.3.6.1.4.1.10106.3.101291.1.1.407
		ham3000c03v1AudStatAes1 OBJECT-TYPE
			SYNTAX BitFail
			MAX-ACCESS read-only
			STATUS current
			DESCRIPTION
				"Indicates audio fail in AES1 input"
		::= { ham3000c03v1Entry 407 }

		-- 1.3.6.1.4.1.10106.3.101291.1.1.408
		ham3000c03v1AudStatAes1TrapEnable OBJECT-TYPE
			SYNTAX AlarmEnable
			MAX-ACCESS read-write
			STATUS current
			DESCRIPTION
				"Indicates audio fail in AES1 input Trap Enable"
		::= { ham3000c03v1Entry 408 }

		-- 1.3.6.1.4.1.10106.3.101291.1.1.409
		ham3000c03v1AudStatAes2 OBJECT-TYPE
			SYNTAX BitFail
			MAX-ACCESS read-only
			STATUS current
			DESCRIPTION
				"Indicates audio fail in AES2 input"
		::= { ham3000c03v1Entry 409 }

		-- 1.3.6.1.4.1.10106.3.101291.1.1.410
		ham3000c03v1AudStatAes2TrapEnable OBJECT-TYPE
			SYNTAX AlarmEnable
			MAX-ACCESS read-write
			STATUS current
			DESCRIPTION
				"Indicates audio fail in AES2 input Trap Enable"
		::= { ham3000c03v1Entry 410 }

		-- 1.3.6.1.4.1.10106.3.101291.1.1.411
		ham3000c03v1OvldPgmOut OBJECT-TYPE
			SYNTAX BitFail
			MAX-ACCESS read-only
			STATUS current
			DESCRIPTION
				"Indicates audio overload in SDI output PGM OUT"
		::= { ham3000c03v1Entry 411 }

		-- 1.3.6.1.4.1.10106.3.101291.1.1.412
		ham3000c03v1OvldPgmOutTrapEnable OBJECT-TYPE
			SYNTAX AlarmEnable
			MAX-ACCESS read-write
			STATUS current
			DESCRIPTION
				"Indicates audio overload in SDI output PGM OUT Trap Enable"
		::= { ham3000c03v1Entry 412 }

		-- 1.3.6.1.4.1.10106.3.101291.1.1.413
		ham3000c03v1OvldAes1Out OBJECT-TYPE
			SYNTAX BitFail
			MAX-ACCESS read-only
			STATUS current
			DESCRIPTION
				"Indicates audio overload in AES1 OUT"
		::= { ham3000c03v1Entry 413 }

		-- 1.3.6.1.4.1.10106.3.101291.1.1.414
		ham3000c03v1OvldAes1OutTrapEnable OBJECT-TYPE
			SYNTAX AlarmEnable
			MAX-ACCESS read-write
			STATUS current
			DESCRIPTION
				"Indicates audio overload in AES1 OUT Trap Enable"
		::= { ham3000c03v1Entry 414 }

		-- 1.3.6.1.4.1.10106.3.101291.1.1.415
		ham3000c03v1OvldAes2Out OBJECT-TYPE
			SYNTAX BitFail
			MAX-ACCESS read-only
			STATUS current
			DESCRIPTION
				"Indicates audio overload in AES2 OUT"
		::= { ham3000c03v1Entry 415 }

		-- 1.3.6.1.4.1.10106.3.101291.1.1.416
		ham3000c03v1OvldAes2OutTrapEnable OBJECT-TYPE
			SYNTAX AlarmEnable
			MAX-ACCESS read-write
			STATUS current
			DESCRIPTION
				"Indicates audio overload in AES2 OUT Trap Enable"
		::= { ham3000c03v1Entry 416 }

		-- 1.3.6.1.4.1.10106.3.101291.1.1.417
		ham3000c03v1OvldAnlg1Out OBJECT-TYPE
			SYNTAX BitFail
			MAX-ACCESS read-only
			STATUS current
			DESCRIPTION
				"Indicates audio overload in ANALOG1 OUT"
		::= { ham3000c03v1Entry 417 }

		-- 1.3.6.1.4.1.10106.3.101291.1.1.418
		ham3000c03v1OvldAnlg1OutTrapEnable OBJECT-TYPE
			SYNTAX AlarmEnable
			MAX-ACCESS read-write
			STATUS current
			DESCRIPTION
				"Indicates audio overload in ANALOG1 OUT Trap Enable"
		::= { ham3000c03v1Entry 418 }

		-- 1.3.6.1.4.1.10106.3.101291.1.1.419
		ham3000c03v1OvldAnlg2Out OBJECT-TYPE
			SYNTAX BitFail
			MAX-ACCESS read-only
			STATUS current
			DESCRIPTION
				"Indicates audio overload in ANALOG2 OUT"
		::= { ham3000c03v1Entry 419 }

		-- 1.3.6.1.4.1.10106.3.101291.1.1.420
		ham3000c03v1OvldAnlg2OutTrapEnable OBJECT-TYPE
			SYNTAX AlarmEnable
			MAX-ACCESS read-write
			STATUS current
			DESCRIPTION
				"Indicates audio overload in ANALOG2 OUT Trap Enable"
		::= { ham3000c03v1Entry 420 }

		-- 1.3.6.1.4.1.10106.3.101291.1.1.421
		ham3000c03v1SilPgmOut OBJECT-TYPE
			SYNTAX BitFail
			MAX-ACCESS read-only
			STATUS current
			DESCRIPTION
				"Indicates audio silence in SDI_PGM_OUT"
		::= { ham3000c03v1Entry 421 }

		-- 1.3.6.1.4.1.10106.3.101291.1.1.422
		ham3000c03v1SilPgmOutTrapEnable OBJECT-TYPE
			SYNTAX AlarmEnable
			MAX-ACCESS read-write
			STATUS current
			DESCRIPTION
				"Indicates audio silence in SDI_PGM_OUT Trap Enable"
		::= { ham3000c03v1Entry 422 }

		-- 1.3.6.1.4.1.10106.3.101291.1.1.423
		ham3000c03v1SilAes1Out OBJECT-TYPE
			SYNTAX BitFail
			MAX-ACCESS read-only
			STATUS current
			DESCRIPTION
				"Indicates audio silence in AES1_OUT"
		::= { ham3000c03v1Entry 423 }

		-- 1.3.6.1.4.1.10106.3.101291.1.1.424
		ham3000c03v1SilAes1OutTrapEnable OBJECT-TYPE
			SYNTAX AlarmEnable
			MAX-ACCESS read-write
			STATUS current
			DESCRIPTION
				"Indicates audio silence in AES1_OUT Trap Enable"
		::= { ham3000c03v1Entry 424 }

		-- 1.3.6.1.4.1.10106.3.101291.1.1.425
		ham3000c03v1SilAes2Out OBJECT-TYPE
			SYNTAX BitFail
			MAX-ACCESS read-only
			STATUS current
			DESCRIPTION
				"Indicates audio silence in AES2_OUT"
		::= { ham3000c03v1Entry 425 }

		-- 1.3.6.1.4.1.10106.3.101291.1.1.426
		ham3000c03v1SilAes2OutTrapEnable OBJECT-TYPE
			SYNTAX AlarmEnable
			MAX-ACCESS read-write
			STATUS current
			DESCRIPTION
				"Indicates audio silence in AES2_OUT Trap Enable"
		::= { ham3000c03v1Entry 426 }

		-- 1.3.6.1.4.1.10106.3.101291.1.1.427
		ham3000c03v1SilAnlg1Out OBJECT-TYPE
			SYNTAX BitFail
			MAX-ACCESS read-only
			STATUS current
			DESCRIPTION
				"Indicates audio silence in ANALOG1_OUT"
		::= { ham3000c03v1Entry 427 }

		-- 1.3.6.1.4.1.10106.3.101291.1.1.428
		ham3000c03v1SilAnlg1OutTrapEnable OBJECT-TYPE
			SYNTAX AlarmEnable
			MAX-ACCESS read-write
			STATUS current
			DESCRIPTION
				"Indicates audio silence in ANALOG1_OUT Trap Enable"
		::= { ham3000c03v1Entry 428 }

		-- 1.3.6.1.4.1.10106.3.101291.1.1.429
		ham3000c03v1SilAnlg2Out OBJECT-TYPE
			SYNTAX BitFail
			MAX-ACCESS read-only
			STATUS current
			DESCRIPTION
				"Indicates audio silence in ANALOG2_OUT"
		::= { ham3000c03v1Entry 429 }

		-- 1.3.6.1.4.1.10106.3.101291.1.1.430
		ham3000c03v1SilAnlg2OutTrapEnable OBJECT-TYPE
			SYNTAX AlarmEnable
			MAX-ACCESS read-write
			STATUS current
			DESCRIPTION
				"Indicates audio silence in ANALOG2_OUT Trap Enable"
		::= { ham3000c03v1Entry 430 }

		-- 1.3.6.1.4.1.10106.3.101291.1.1.431
		ham3000c03v1SerialNo OBJECT-TYPE
			SYNTAX SerialNo
			MAX-ACCESS read-only
			STATUS current
			DESCRIPTION
				"Serial number"
		::= { ham3000c03v1Entry 431 }

		-- 1.3.6.1.4.1.10106.3.101291.1.1.433
		ham3000c03v1SavePreset OBJECT-TYPE
			SYNTAX Preset16Save
			MAX-ACCESS read-write
			STATUS current
			DESCRIPTION
				"Allows saving a preset"
		::= { ham3000c03v1Entry 433 }

		-- 1.3.6.1.4.1.10106.3.101291.1.1.435
		ham3000c03v1VidAuxSel OBJECT-TYPE
			SYNTAX Bit0Aux1Pgm
			MAX-ACCESS read-write
			STATUS current
			DESCRIPTION
				"Allows selecting the auxiliar input beetween the AUX IN and the PGM IN"
		::= { ham3000c03v1Entry 435 }

		-- 1.3.6.1.4.1.10106.3.412201
		hop3147c02v1 OBJECT IDENTIFIER ::= { albalaProducts 412201 }

		-- 1.3.6.1.4.1.10106.3.412201.1
		hop3147c02v1Table  OBJECT-TYPE
			SYNTAX SEQUENCE OF Hop3147c02v1Entry
			MAX-ACCESS not-accessible
			STATUS current
			DESCRIPTION
				"Module  HOP3147C02V1 Table"
			::= { hop3147c02v1 1 }

		-- 1.3.6.1.4.1.10106.3.412201.1.1
		hop3147c02v1Entry  OBJECT-TYPE
			SYNTAX Hop3147c02v1Entry
			MAX-ACCESS not-accessible
			STATUS current
			DESCRIPTION
				"Module HOP3147C02V1 Entry"
			INDEX { hop3147c02v1Index }
			::= { hop3147c02v1Table 1 }

			Hop3147c02v1Entry ::=
			SEQUENCE {
				hop3147c02v1Index
				ModuleIndex,
				hop3147c02v1ActivePreset
				Preset16Active,
				hop3147c02v1LoadPreset
				Preset16Load,
				hop3147c02v1SavePreset
				Preset16Save,
				hop3147c02v1TxtInsEna1
				BitMask,
				hop3147c02v1TxtInsEna2
				BitMask,
				hop3147c02v1Op47InsEna
				BitMask,
				hop3147c02v1TxtCleanEna1
				BitMask,
				hop3147c02v1TxtCleanEna2
				BitMask,
				hop3147c02v1Op47CleanEna
				BitMask,
				hop3147c02v1Gpo8SigFail
				Bit0No1Yes,
				hop3147c02v1Op47PckInsLin
				Uint5,
				hop3147c02v1TxtInsLine1
				Uint5,
				hop3147c02v1TxtInsLine2
				Uint5,
				hop3147c02v1TxtRdLine
				Uint5,
				hop3147c02v1TxtRdEna
				BitMask,
				hop3147c02v1InvertGpi1Pol
				Bit0No1Yes,
				hop3147c02v1InvertGpi2Pol
				Bit0No1Yes,
				hop3147c02v1InvertGpi3Pol
				Bit0No1Yes,
				hop3147c02v1InvertGpi4Pol
				Bit0No1Yes,
				hop3147c02v1InvertGpi5Pol
				Bit0No1Yes,
				hop3147c02v1InvertGpi6Pol
				Bit0No1Yes,
				hop3147c02v1InvertGpi7Pol
				Bit0No1Yes,
				hop3147c02v1InvertGpi8Pol
				Bit0No1Yes,
				hop3147c02v1InvertGpo1Pol
				Bit0No1Yes,
				hop3147c02v1InvertGpo2Pol
				Bit0No1Yes,
				hop3147c02v1InvertGpo3Pol
				Bit0No1Yes,
				hop3147c02v1InvertGpo4Pol
				Bit0No1Yes,
				hop3147c02v1InvertGpo5Pol
				Bit0No1Yes,
				hop3147c02v1InvertGpo6Pol
				Bit0No1Yes,
				hop3147c02v1InvertGpo7Pol
				Bit0No1Yes,
				hop3147c02v1InvertGpo8Pol
				Bit0No1Yes,
				hop3147c02v1TxtInsA
				Bit0No1Yes,
				hop3147c02v1TxtInsB
				Bit0No1Yes,
				hop3147c02v1TxtInsFrstLin
				Bit0No1Yes,
				hop3147c02v1TxtInsHidenCh
				Bit0No1Yes,
				hop3147c02v1TxtInsPage
				Uint16,
				hop3147c02v1TxtBridgeEn
				BitMask,
				hop3147c02v1InsAudioEn
				BitMask,
				hop3147c02v1InsAudPair
				AudioMxInput6,
				hop3147c02v1RdAudEn
				BitMask,
				hop3147c02v1RdAudChn
				AudioMxInput6,
				hop3147c02v1CleanAudChnEn
				BitMask,
				hop3147c02v1GposSrc
				HopGpoSrcSel,
				hop3147c02v1VitcBridgeEn
				Bit0No1Yes,
				hop3147c02v1KeepSdLinVitc
				BitMask,
				hop3147c02v1SdLineVitc
				Uint5,
				hop3147c02v1KeepDupVitc
				BitMask,
				hop3147c02v1DupVitc
				BitMask,
				hop3147c02v1ViiInsEn
				Bit0No1Yes,
				hop3147c02v1WssInsEn
				Bit0No1Yes,
				hop3147c02v1AfdInsEn
				Bit0No1Yes,
				hop3147c02v1AfdAr
				Cf1,
				hop3147c02v1AfdD
				Uint4X,
				hop3147c02v1AncInsL1En
				Bit0No1Yes,
				hop3147c02v1AncInsL2En
				Bit0No1Yes,
				hop3147c02v1AncInsActVid
				Bit0Hrz1Av,
				hop3147c02v1AncInsLumNCr
				Bit0Chr1Lum,
				hop3147c02v1AncInsPckNum
				Uint3,
				hop3147c02v1AncInsL1
				Uint11,
				hop3147c02v1AncInsL2
				Uint11,
				hop3147c02v1AncInsRepet
				AncInserterRep,
				hop3147c02v1GpisInvPrst1
				Bit0No1Yes,
				hop3147c02v1GpisInvPrst2
				Bit0No1Yes,
				hop3147c02v1GpisInvPrst3
				Bit0No1Yes,
				hop3147c02v1GpisInvPrst4
				Bit0No1Yes,
				hop3147c02v1GpisInvPrst5
				Bit0No1Yes,
				hop3147c02v1GpisInvPrst6
				Bit0No1Yes,
				hop3147c02v1GpisInvPrst7
				Bit0No1Yes,
				hop3147c02v1GpisInvPrst8
				Bit0No1Yes,
				hop3147c02v1TxtBridgeEn0
				Bit0No1Yes,
				hop3147c02v1TxtBridgeEn1
				Bit0No1Yes,
				hop3147c02v1TxtBridgeEn2
				Bit0No1Yes,
				hop3147c02v1TxtBridgeEn3
				Bit0No1Yes,
				hop3147c02v1TxtBridgeEn4
				Bit0No1Yes,
				hop3147c02v1TxtBridgeEn5
				Bit0No1Yes,
				hop3147c02v1TxtBridgeEn6
				Bit0No1Yes,
				hop3147c02v1TxtBridgeEn7
				Bit0No1Yes,
				hop3147c02v1TxtBridgeEn8
				Bit0No1Yes,
				hop3147c02v1TxtBridgeEn9
				Bit0No1Yes,
				hop3147c02v1TxtBridgeEn10
				Bit0No1Yes,
				hop3147c02v1TxtBridgeEn11
				Bit0No1Yes,
				hop3147c02v1TxtBridgeEn12
				Bit0No1Yes,
				hop3147c02v1TxtBridgeEn13
				Bit0No1Yes,
				hop3147c02v1TxtBridgeEn14
				Bit0No1Yes,
				hop3147c02v1TxtBridgeEn15
				Bit0No1Yes,
				hop3147c02v1TxtBridgeEn16
				Bit0No1Yes,
				hop3147c02v1TxtBridgeEn17
				Bit0No1Yes,
				hop3147c02v1TxtBridgeEn18
				Bit0No1Yes,
				hop3147c02v1TxtBridgeEn19
				Bit0No1Yes,
				hop3147c02v1TxtBridgeEn20
				Bit0No1Yes,
				hop3147c02v1TxtBridgeEn21
				Bit0No1Yes,
				hop3147c02v1TxtBridgeEn22
				Bit0No1Yes,
				hop3147c02v1TxtBridgeEn23
				Bit0No1Yes,
				hop3147c02v1TxtBridgeEn24
				Bit0No1Yes,
				hop3147c02v1TxtBridgeEn25
				Bit0No1Yes,
				hop3147c02v1TxtBridgeEn26
				Bit0No1Yes,
				hop3147c02v1TxtBridgeEn27
				Bit0No1Yes,
				hop3147c02v1TxtBridgeEn28
				Bit0No1Yes,
				hop3147c02v1TxtBridgeEn29
				Bit0No1Yes,
				hop3147c02v1TxtBridgeEn30
				Bit0No1Yes,
				hop3147c02v1TxtBridgeEn31
				Bit0No1Yes,
				hop3147c02v1TxtBridge0
				TxtBridgeLine,
				hop3147c02v1TxtBridge1
				TxtBridgeLine,
				hop3147c02v1TxtBridge2
				TxtBridgeLine,
				hop3147c02v1TxtBridge3
				TxtBridgeLine,
				hop3147c02v1TxtBridge4
				TxtBridgeLine,
				hop3147c02v1TxtBridge5
				TxtBridgeLine,
				hop3147c02v1TxtBridge6
				TxtBridgeLine,
				hop3147c02v1TxtBridge7
				TxtBridgeLine,
				hop3147c02v1TxtBridge8
				TxtBridgeLine,
				hop3147c02v1TxtBridge9
				TxtBridgeLine,
				hop3147c02v1TxtBridge10
				TxtBridgeLine,
				hop3147c02v1TxtBridge11
				TxtBridgeLine,
				hop3147c02v1TxtBridge12
				TxtBridgeLine,
				hop3147c02v1TxtBridge13
				TxtBridgeLine,
				hop3147c02v1TxtBridge14
				TxtBridgeLine,
				hop3147c02v1TxtBridge15
				TxtBridgeLine,
				hop3147c02v1TxtBridge16
				TxtBridgeLine,
				hop3147c02v1TxtBridge17
				TxtBridgeLine,
				hop3147c02v1TxtBridge18
				TxtBridgeLine,
				hop3147c02v1TxtBridge19
				TxtBridgeLine,
				hop3147c02v1TxtBridge20
				TxtBridgeLine,
				hop3147c02v1TxtBridge21
				TxtBridgeLine,
				hop3147c02v1TxtBridge22
				TxtBridgeLine,
				hop3147c02v1TxtBridge23
				TxtBridgeLine,
				hop3147c02v1TxtBridge24
				TxtBridgeLine,
				hop3147c02v1TxtBridge25
				TxtBridgeLine,
				hop3147c02v1TxtBridge26
				TxtBridgeLine,
				hop3147c02v1TxtBridge27
				TxtBridgeLine,
				hop3147c02v1TxtBridge28
				TxtBridgeLine,
				hop3147c02v1TxtBridge29
				TxtBridgeLine,
				hop3147c02v1TxtBridge30
				TxtBridgeLine,
				hop3147c02v1TxtBridge31
				TxtBridgeLine,
				hop3147c02v1TxtBridgeOp47
				Uint8,
				hop3147c02v1TxtFail
				BitFail,
				hop3147c02v1TxtFailTrapEnable
				AlarmEnable,
				hop3147c02v1TxtInsFail
				BitFail,
				hop3147c02v1TxtInsFailTrapEnable
				AlarmEnable,
				hop3147c02v1AudioFail
				BitFail,
				hop3147c02v1AudioFailTrapEnable
				AlarmEnable,
				hop3147c02v1AudioInsFail
				BitFail,
				hop3147c02v1AudioInsFailTrapEnable
				AlarmEnable,
				hop3147c02v1ViiInsFail
				BitFail,
				hop3147c02v1ViiInsFailTrapEnable
				AlarmEnable,
				hop3147c02v1WssInsFail
				BitFail,
				hop3147c02v1WssInsFailTrapEnable
				AlarmEnable,
				hop3147c02v1AfdInsFail
				BitFail,
				hop3147c02v1AfdInsFailTrapEnable
				AlarmEnable,
				hop3147c02v1NoSignal0
				BitFail,
				hop3147c02v1NoSignal0TrapEnable
				AlarmEnable,
				hop3147c02v1Unlocked0
				BitFail,
				hop3147c02v1Unlocked0TrapEnable
				AlarmEnable,
				hop3147c02v1EdhCrc0
				BitFail,
				hop3147c02v1EdhCrc0TrapEnable
				AlarmEnable,
				hop3147c02v1Format0
				SdiHd3gFmt3,
				hop3147c02v1NoSignal1
				BitFail,
				hop3147c02v1NoSignal1TrapEnable
				AlarmEnable,
				hop3147c02v1Unlocked1
				BitFail,
				hop3147c02v1Unlocked1TrapEnable
				AlarmEnable,
				hop3147c02v1EdhCrc1
				BitFail,
				hop3147c02v1EdhCrc1TrapEnable
				AlarmEnable,
				hop3147c02v1Format1
				SdiHd3gFmt3,
				hop3147c02v1Gpi1
				Bit0Off1On,
				hop3147c02v1Gpi1TrapEnable
				AlarmEnable,
				hop3147c02v1Gpi2
				Bit0Off1On,
				hop3147c02v1Gpi2TrapEnable
				AlarmEnable,
				hop3147c02v1Gpi3
				Bit0Off1On,
				hop3147c02v1Gpi3TrapEnable
				AlarmEnable,
				hop3147c02v1Gpi4
				Bit0Off1On,
				hop3147c02v1Gpi4TrapEnable
				AlarmEnable,
				hop3147c02v1Gpi5
				Bit0Off1On,
				hop3147c02v1Gpi5TrapEnable
				AlarmEnable,
				hop3147c02v1Gpi6
				Bit0Off1On,
				hop3147c02v1Gpi6TrapEnable
				AlarmEnable,
				hop3147c02v1Gpi7
				Bit0Off1On,
				hop3147c02v1Gpi7TrapEnable
				AlarmEnable,
				hop3147c02v1Gpi8
				Bit0Off1On,
				hop3147c02v1Gpi8TrapEnable
				AlarmEnable,
				hop3147c02v1Gpo1
				Bit0Off1On,
				hop3147c02v1Gpo1TrapEnable
				AlarmEnable,
				hop3147c02v1Gpo2
				Bit0Off1On,
				hop3147c02v1Gpo2TrapEnable
				AlarmEnable,
				hop3147c02v1Gpo3
				Bit0Off1On,
				hop3147c02v1Gpo3TrapEnable
				AlarmEnable,
				hop3147c02v1Gpo4
				Bit0Off1On,
				hop3147c02v1Gpo4TrapEnable
				AlarmEnable,
				hop3147c02v1Gpo5
				Bit0Off1On,
				hop3147c02v1Gpo5TrapEnable
				AlarmEnable,
				hop3147c02v1Gpo6
				Bit0Off1On,
				hop3147c02v1Gpo6TrapEnable
				AlarmEnable,
				hop3147c02v1Gpo7
				Bit0Off1On,
				hop3147c02v1Gpo7TrapEnable
				AlarmEnable,
				hop3147c02v1Gpo8
				Bit0Off1On,
				hop3147c02v1Gpo8TrapEnable
				AlarmEnable,
				hop3147c02v1VitcAtcPres
				BitFailN,
				hop3147c02v1VitcAtcPresTrapEnable
				AlarmEnable,
				hop3147c02v1TxtAuxPres
				BitFailN,
				hop3147c02v1TxtAuxPresTrapEnable
				AlarmEnable,
				hop3147c02v1TxtPres
				BitFailN,
				hop3147c02v1TxtPresTrapEnable
				AlarmEnable,
				hop3147c02v1AncInsL1Ok
				BitFail,
				hop3147c02v1AncInsL2Ok
				BitFail,
				hop3147c02v1SerialNo
				SerialNo,
				hop3147c02v1SplStartInmEn
				Bit0No1Yes,
				hop3147c02v1SplEndInmEn
				Bit0No1Yes,
				hop3147c02v1SplStartNorEn
				Bit0No1Yes,
				hop3147c02v1SplEndNorEn
				Bit0No1Yes,
				hop3147c02v1Scte104StNDyn
				Bit0No1Yes,
				hop3147c02v1Scte104AretTx
				Bit0No1Yes,
				hop3147c02v1Scte104RxAck
				Bit0No1Yes,
				hop3147c02v1Scte104RxAsEn
				Bit0No1Yes,
				hop3147c02v1Scte104RxAsFi
				Uint8,
				hop3147c02v1Scte104TxAsId
				Uint8,
				hop3147c02v1Scte104Line
				Uint6,
				hop3147c02v1Scte104PreRoll
				PreRoll,
				hop3147c02v1Scte104TxBrkds
				BreakDuration,
				hop3147c02v1Scte104TxBrkdd
				BreakDuration,
				hop3147c02v1Scte104InsF
				BitFail,
				hop3147c02v1Scte104RxF
				BitFail,
				hop3147c02v1Scte104Status
				Bit0Off1On,
				hop3147c02v1Scte104AretRx
				Bit0Off1On,
				hop3147c02v1Scte104RxPck
				Scte104PckType,
				hop3147c02v1Scte104RxAsId
				Uint8,
				hop3147c02v1Scte104RxPrRo
				PreRoll,
				hop3147c02v1Scte104RxBrkd
				BreakDuration,
				hop3147c02v1Scte104ContRx
				Uint8,
				hop3147c02v1LtcInsEn
				VitcLtc,
				hop3147c02v1DtmfInsEn
				Bit0No1Yes,
				hop3147c02v1DtmfGpi5En
				Bit0No1Yes,
				hop3147c02v1DtmfGpi6En
				Bit0No1Yes,
				hop3147c02v1DtmfGpi7En
				Bit0No1Yes,
				hop3147c02v1DtmfGpi8En
				Bit0No1Yes,
				hop3147c02v1DtmfChannel
				AudioMxInput6,
				hop3147c02v1DtmfPairEn
				Bit0No1Yes,
				hop3147c02v1DtmfLevel
				LevelDbfsF,
				hop3147c02v1DtmfCode11
				DtmfCode,
				hop3147c02v1DtmfCode12
				DtmfCode,
				hop3147c02v1DtmfCode13
				DtmfCode,
				hop3147c02v1DtmfCode14
				DtmfCode,
				hop3147c02v1DtmfCode21
				DtmfCode,
				hop3147c02v1DtmfCode22
				DtmfCode,
				hop3147c02v1DtmfCode23
				DtmfCode,
				hop3147c02v1DtmfCode24
				DtmfCode,
				hop3147c02v1DtmfCode31
				DtmfCode,
				hop3147c02v1DtmfCode32
				DtmfCode,
				hop3147c02v1DtmfCode33
				DtmfCode,
				hop3147c02v1DtmfCode34
				DtmfCode,
				hop3147c02v1DtmfCode41
				DtmfCode,
				hop3147c02v1DtmfCode42
				DtmfCode,
				hop3147c02v1DtmfCode43
				DtmfCode,
				hop3147c02v1DtmfCode44
				DtmfCode,
				hop3147c02v1InsCode1
				Bit0No1Yes,
				hop3147c02v1InsCode2
				Bit0No1Yes,
				hop3147c02v1InsCode3
				Bit0No1Yes,
				hop3147c02v1InsCode4
				Bit0No1Yes,
				hop3147c02v1Scte104Ins
				Scte104Interva,
				hop3147c02v1SplStInmInEn
				Bit0No1Yes,
				hop3147c02v1SplStEndInEn
				Bit0No1Yes,
				hop3147c02v1Gpi7SplStaOn
				Bit0No1Yes,
				hop3147c02v1Gpi8SplStaOff
				Bit0No1Yes
			 }

		-- 1.3.6.1.4.1.10106.3.101291.1.1.1
		hop3147c02v1Index OBJECT-TYPE
			SYNTAX ModuleIndex
			MAX-ACCESS read-only
			STATUS current
			DESCRIPTION
				"Index of HOP3147C02V1 Table"
		::= { hop3147c02v1Entry 1 }

		-- 1.3.6.1.4.1.10106.3.101291.1.1.3
		hop3147c02v1ActivePreset OBJECT-TYPE
			SYNTAX Preset16Active
			MAX-ACCESS read-only
			STATUS current
			DESCRIPTION
				"Shows the active preset"
		::= { hop3147c02v1Entry 3 }

		-- 1.3.6.1.4.1.10106.3.101291.1.1.5
		hop3147c02v1LoadPreset OBJECT-TYPE
			SYNTAX Preset16Load
			MAX-ACCESS read-write
			STATUS current
			DESCRIPTION
				"Allows loading a preset"
		::= { hop3147c02v1Entry 5 }

		-- 1.3.6.1.4.1.10106.3.101291.1.1.7
		hop3147c02v1SavePreset OBJECT-TYPE
			SYNTAX Preset16Save
			MAX-ACCESS read-write
			STATUS current
			DESCRIPTION
				"Allows saving a preset"
		::= { hop3147c02v1Entry 7 }

		-- 1.3.6.1.4.1.10106.3.101291.1.1.9
		hop3147c02v1TxtInsEna1 OBJECT-TYPE
			SYNTAX BitMask
			MAX-ACCESS read-write
			STATUS current
			DESCRIPTION
				"Enables insertion in SD_L1"
		::= { hop3147c02v1Entry 9 }

		-- 1.3.6.1.4.1.10106.3.101291.1.1.11
		hop3147c02v1TxtInsEna2 OBJECT-TYPE
			SYNTAX BitMask
			MAX-ACCESS read-write
			STATUS current
			DESCRIPTION
				"Enables insertion in SD_L2"
		::= { hop3147c02v1Entry 11 }

		-- 1.3.6.1.4.1.10106.3.101291.1.1.13
		hop3147c02v1Op47InsEna OBJECT-TYPE
			SYNTAX BitMask
			MAX-ACCESS read-write
			STATUS current
			DESCRIPTION
				"Enables insertion in HD"
		::= { hop3147c02v1Entry 13 }

		-- 1.3.6.1.4.1.10106.3.101291.1.1.15
		hop3147c02v1TxtCleanEna1 OBJECT-TYPE
			SYNTAX BitMask
			MAX-ACCESS read-write
			STATUS current
			DESCRIPTION
				"Enables cleaning active part of a line to remove teletext data"
		::= { hop3147c02v1Entry 15 }

		-- 1.3.6.1.4.1.10106.3.101291.1.1.17
		hop3147c02v1TxtCleanEna2 OBJECT-TYPE
			SYNTAX BitMask
			MAX-ACCESS read-write
			STATUS current
			DESCRIPTION
				"Enables cleaning active part of a line to remove teletext data"
		::= { hop3147c02v1Entry 17 }

		-- 1.3.6.1.4.1.10106.3.101291.1.1.19
		hop3147c02v1Op47CleanEna OBJECT-TYPE
			SYNTAX BitMask
			MAX-ACCESS read-write
			STATUS current
			DESCRIPTION
				"Enables cleaning active part of a line to remove OP47"
		::= { hop3147c02v1Entry 19 }

		-- 1.3.6.1.4.1.10106.3.101291.1.1.21
		hop3147c02v1Gpo8SigFail OBJECT-TYPE
			SYNTAX Bit0No1Yes
			MAX-ACCESS read-write
			STATUS current
			DESCRIPTION
				"GPO8 used to signal fail in teletext"
		::= { hop3147c02v1Entry 21 }

		-- 1.3.6.1.4.1.10106.3.101291.1.1.23
		hop3147c02v1Op47PckInsLin OBJECT-TYPE
			SYNTAX Uint5
			MAX-ACCESS read-write
			STATUS current
			DESCRIPTION
				"HD insertion line (OP47 packet)"
		::= { hop3147c02v1Entry 23 }

		-- 1.3.6.1.4.1.10106.3.101291.1.1.25
		hop3147c02v1TxtInsLine1 OBJECT-TYPE
			SYNTAX Uint5
			MAX-ACCESS read-write
			STATUS current
			DESCRIPTION
				"SD_L1 insertion line (Teletext A)"
		::= { hop3147c02v1Entry 25 }

		-- 1.3.6.1.4.1.10106.3.101291.1.1.27
		hop3147c02v1TxtInsLine2 OBJECT-TYPE
			SYNTAX Uint5
			MAX-ACCESS read-write
			STATUS current
			DESCRIPTION
				"SD_L2 insertion line (Teletext B)"
		::= { hop3147c02v1Entry 27 }

		-- 1.3.6.1.4.1.10106.3.101291.1.1.29
		hop3147c02v1TxtRdLine OBJECT-TYPE
			SYNTAX Uint5
			MAX-ACCESS read-write
			STATUS current
			DESCRIPTION
				"Teletext read line"
		::= { hop3147c02v1Entry 29 }

		-- 1.3.6.1.4.1.10106.3.101291.1.1.31
		hop3147c02v1TxtRdEna OBJECT-TYPE
			SYNTAX BitMask
			MAX-ACCESS read-write
			STATUS current
			DESCRIPTION
				"Enables reading Teletext"
		::= { hop3147c02v1Entry 31 }

		-- 1.3.6.1.4.1.10106.3.101291.1.1.33
		hop3147c02v1InvertGpi1Pol OBJECT-TYPE
			SYNTAX Bit0No1Yes
			MAX-ACCESS read-write
			STATUS current
			DESCRIPTION
				"Changes GPI1 polarity to normally closed"
		::= { hop3147c02v1Entry 33 }

		-- 1.3.6.1.4.1.10106.3.101291.1.1.35
		hop3147c02v1InvertGpi2Pol OBJECT-TYPE
			SYNTAX Bit0No1Yes
			MAX-ACCESS read-write
			STATUS current
			DESCRIPTION
				"Changes GPI2 polarity to normally closed"
		::= { hop3147c02v1Entry 35 }

		-- 1.3.6.1.4.1.10106.3.101291.1.1.37
		hop3147c02v1InvertGpi3Pol OBJECT-TYPE
			SYNTAX Bit0No1Yes
			MAX-ACCESS read-write
			STATUS current
			DESCRIPTION
				"Changes GPI3 polarity to normally closed"
		::= { hop3147c02v1Entry 37 }

		-- 1.3.6.1.4.1.10106.3.101291.1.1.39
		hop3147c02v1InvertGpi4Pol OBJECT-TYPE
			SYNTAX Bit0No1Yes
			MAX-ACCESS read-write
			STATUS current
			DESCRIPTION
				"Changes GPI4 polarity to normally closed"
		::= { hop3147c02v1Entry 39 }

		-- 1.3.6.1.4.1.10106.3.101291.1.1.41
		hop3147c02v1InvertGpi5Pol OBJECT-TYPE
			SYNTAX Bit0No1Yes
			MAX-ACCESS read-write
			STATUS current
			DESCRIPTION
				"Changes GPI5 polarity to normally closed"
		::= { hop3147c02v1Entry 41 }

		-- 1.3.6.1.4.1.10106.3.101291.1.1.43
		hop3147c02v1InvertGpi6Pol OBJECT-TYPE
			SYNTAX Bit0No1Yes
			MAX-ACCESS read-write
			STATUS current
			DESCRIPTION
				"Changes GPI6 polarity to normally closed"
		::= { hop3147c02v1Entry 43 }

		-- 1.3.6.1.4.1.10106.3.101291.1.1.45
		hop3147c02v1InvertGpi7Pol OBJECT-TYPE
			SYNTAX Bit0No1Yes
			MAX-ACCESS read-write
			STATUS current
			DESCRIPTION
				"Changes GPI7 polarity to normally closed"
		::= { hop3147c02v1Entry 45 }

		-- 1.3.6.1.4.1.10106.3.101291.1.1.47
		hop3147c02v1InvertGpi8Pol OBJECT-TYPE
			SYNTAX Bit0No1Yes
			MAX-ACCESS read-write
			STATUS current
			DESCRIPTION
				"Changes GPI8 polarity to normally closed"
		::= { hop3147c02v1Entry 47 }

		-- 1.3.6.1.4.1.10106.3.101291.1.1.49
		hop3147c02v1InvertGpo1Pol OBJECT-TYPE
			SYNTAX Bit0No1Yes
			MAX-ACCESS read-write
			STATUS current
			DESCRIPTION
				"Changes GPO1 polarity to normally closed"
		::= { hop3147c02v1Entry 49 }

		-- 1.3.6.1.4.1.10106.3.101291.1.1.51
		hop3147c02v1InvertGpo2Pol OBJECT-TYPE
			SYNTAX Bit0No1Yes
			MAX-ACCESS read-write
			STATUS current
			DESCRIPTION
				"Changes GPO2 polarity to normally closed"
		::= { hop3147c02v1Entry 51 }

		-- 1.3.6.1.4.1.10106.3.101291.1.1.53
		hop3147c02v1InvertGpo3Pol OBJECT-TYPE
			SYNTAX Bit0No1Yes
			MAX-ACCESS read-write
			STATUS current
			DESCRIPTION
				"Changes GPO3 polarity to normally closed"
		::= { hop3147c02v1Entry 53 }

		-- 1.3.6.1.4.1.10106.3.101291.1.1.55
		hop3147c02v1InvertGpo4Pol OBJECT-TYPE
			SYNTAX Bit0No1Yes
			MAX-ACCESS read-write
			STATUS current
			DESCRIPTION
				"Changes GPO4 polarity to normally closed"
		::= { hop3147c02v1Entry 55 }

		-- 1.3.6.1.4.1.10106.3.101291.1.1.57
		hop3147c02v1InvertGpo5Pol OBJECT-TYPE
			SYNTAX Bit0No1Yes
			MAX-ACCESS read-write
			STATUS current
			DESCRIPTION
				"Changes GPO5 polarity to normally closed"
		::= { hop3147c02v1Entry 57 }

		-- 1.3.6.1.4.1.10106.3.101291.1.1.59
		hop3147c02v1InvertGpo6Pol OBJECT-TYPE
			SYNTAX Bit0No1Yes
			MAX-ACCESS read-write
			STATUS current
			DESCRIPTION
				"Changes GPO6 polarity to normally closed"
		::= { hop3147c02v1Entry 59 }

		-- 1.3.6.1.4.1.10106.3.101291.1.1.61
		hop3147c02v1InvertGpo7Pol OBJECT-TYPE
			SYNTAX Bit0No1Yes
			MAX-ACCESS read-write
			STATUS current
			DESCRIPTION
				"Changes GPO7 polarity to normally closed"
		::= { hop3147c02v1Entry 61 }

		-- 1.3.6.1.4.1.10106.3.101291.1.1.63
		hop3147c02v1InvertGpo8Pol OBJECT-TYPE
			SYNTAX Bit0No1Yes
			MAX-ACCESS read-write
			STATUS current
			DESCRIPTION
				"Changes GPO8 polarity to normally closed"
		::= { hop3147c02v1Entry 63 }

		-- 1.3.6.1.4.1.10106.3.101291.1.1.65
		hop3147c02v1TxtInsA OBJECT-TYPE
			SYNTAX Bit0No1Yes
			MAX-ACCESS read-write
			STATUS current
			DESCRIPTION
				"OSD Teletext in OUT A"
		::= { hop3147c02v1Entry 65 }

		-- 1.3.6.1.4.1.10106.3.101291.1.1.67
		hop3147c02v1TxtInsB OBJECT-TYPE
			SYNTAX Bit0No1Yes
			MAX-ACCESS read-write
			STATUS current
			DESCRIPTION
				"OSD Teletext in OUT B"
		::= { hop3147c02v1Entry 67 }

		-- 1.3.6.1.4.1.10106.3.101291.1.1.69
		hop3147c02v1TxtInsFrstLin OBJECT-TYPE
			SYNTAX Bit0No1Yes
			MAX-ACCESS read-write
			STATUS current
			DESCRIPTION
				"Teletext first line insertion"
		::= { hop3147c02v1Entry 69 }

		-- 1.3.6.1.4.1.10106.3.101291.1.1.71
		hop3147c02v1TxtInsHidenCh OBJECT-TYPE
			SYNTAX Bit0No1Yes
			MAX-ACCESS read-write
			STATUS current
			DESCRIPTION
				"Teletext hidden characters insertion"
		::= { hop3147c02v1Entry 71 }

		-- 1.3.6.1.4.1.10106.3.101291.1.1.73
		hop3147c02v1TxtInsPage OBJECT-TYPE
			SYNTAX Uint16
			MAX-ACCESS read-write
			STATUS current
			DESCRIPTION
				"Teletext insertion page"
		::= { hop3147c02v1Entry 73 }

		-- 1.3.6.1.4.1.10106.3.101291.1.1.75
		hop3147c02v1TxtBridgeEn OBJECT-TYPE
			SYNTAX BitMask
			MAX-ACCESS read-write
			STATUS current
			DESCRIPTION
				"Teletext bridge enable"
		::= { hop3147c02v1Entry 75 }

		-- 1.3.6.1.4.1.10106.3.101291.1.1.77
		hop3147c02v1InsAudioEn OBJECT-TYPE
			SYNTAX BitMask
			MAX-ACCESS read-write
			STATUS current
			DESCRIPTION
				"Audio insertion enable"
		::= { hop3147c02v1Entry 77 }

		-- 1.3.6.1.4.1.10106.3.101291.1.1.79
		hop3147c02v1InsAudPair OBJECT-TYPE
			SYNTAX AudioMxInput6
			MAX-ACCESS read-write
			STATUS current
			DESCRIPTION
				"Channel insertion selection"
		::= { hop3147c02v1Entry 79 }

		-- 1.3.6.1.4.1.10106.3.101291.1.1.81
		hop3147c02v1RdAudEn OBJECT-TYPE
			SYNTAX BitMask
			MAX-ACCESS read-write
			STATUS current
			DESCRIPTION
				"Audio read enable"
		::= { hop3147c02v1Entry 81 }

		-- 1.3.6.1.4.1.10106.3.101291.1.1.83
		hop3147c02v1RdAudChn OBJECT-TYPE
			SYNTAX AudioMxInput6
			MAX-ACCESS read-write
			STATUS current
			DESCRIPTION
				"Channel read selection"
		::= { hop3147c02v1Entry 83 }

		-- 1.3.6.1.4.1.10106.3.101291.1.1.85
		hop3147c02v1CleanAudChnEn OBJECT-TYPE
			SYNTAX BitMask
			MAX-ACCESS read-write
			STATUS current
			DESCRIPTION
				"Clean readed audio channel"
		::= { hop3147c02v1Entry 85 }

		-- 1.3.6.1.4.1.10106.3.101291.1.1.87
		hop3147c02v1GposSrc OBJECT-TYPE
			SYNTAX HopGpoSrcSel
			MAX-ACCESS read-write
			STATUS current
			DESCRIPTION
				"Indicates what source of information is used to control GPO's"
		::= { hop3147c02v1Entry 87 }

		-- 1.3.6.1.4.1.10106.3.101291.1.1.89
		hop3147c02v1VitcBridgeEn OBJECT-TYPE
			SYNTAX Bit0No1Yes
			MAX-ACCESS read-write
			STATUS current
			DESCRIPTION
				"VITC-ATC bridge enable"
		::= { hop3147c02v1Entry 89 }

		-- 1.3.6.1.4.1.10106.3.101291.1.1.91
		hop3147c02v1KeepSdLinVitc OBJECT-TYPE
			SYNTAX BitMask
			MAX-ACCESS read-write
			STATUS current
			DESCRIPTION
				"Keep VITC insertion line"
		::= { hop3147c02v1Entry 91 }

		-- 1.3.6.1.4.1.10106.3.101291.1.1.93
		hop3147c02v1SdLineVitc OBJECT-TYPE
			SYNTAX Uint5
			MAX-ACCESS read-write
			STATUS current
			DESCRIPTION
				"VITC insertion line"
		::= { hop3147c02v1Entry 93 }

		-- 1.3.6.1.4.1.10106.3.101291.1.1.95
		hop3147c02v1KeepDupVitc OBJECT-TYPE
			SYNTAX BitMask
			MAX-ACCESS read-write
			STATUS current
			DESCRIPTION
				"Keep VITC line duplication"
		::= { hop3147c02v1Entry 95 }

		-- 1.3.6.1.4.1.10106.3.101291.1.1.97
		hop3147c02v1DupVitc OBJECT-TYPE
			SYNTAX BitMask
			MAX-ACCESS read-write
			STATUS current
			DESCRIPTION
				"VITC line duplication"
		::= { hop3147c02v1Entry 97 }

		-- 1.3.6.1.4.1.10106.3.101291.1.1.99
		hop3147c02v1ViiInsEn OBJECT-TYPE
			SYNTAX Bit0No1Yes
			MAX-ACCESS read-write
			STATUS current
			DESCRIPTION
				"VII insertion (SD only)"
		::= { hop3147c02v1Entry 99 }

		-- 1.3.6.1.4.1.10106.3.101291.1.1.101
		hop3147c02v1WssInsEn OBJECT-TYPE
			SYNTAX Bit0No1Yes
			MAX-ACCESS read-write
			STATUS current
			DESCRIPTION
				"WSS insertion (SD only)"
		::= { hop3147c02v1Entry 101 }

		-- 1.3.6.1.4.1.10106.3.101291.1.1.103
		hop3147c02v1AfdInsEn OBJECT-TYPE
			SYNTAX Bit0No1Yes
			MAX-ACCESS read-write
			STATUS current
			DESCRIPTION
				"AFD insertion (SMPTE 2016-3)"
		::= { hop3147c02v1Entry 103 }

		-- 1.3.6.1.4.1.10106.3.101291.1.1.105
		hop3147c02v1AfdAr OBJECT-TYPE
			SYNTAX Cf1
			MAX-ACCESS read-write
			STATUS current
			DESCRIPTION
				"Code aspect ratio"
		::= { hop3147c02v1Entry 105 }

		-- 1.3.6.1.4.1.10106.3.101291.1.1.107
		hop3147c02v1AfdD OBJECT-TYPE
			SYNTAX Uint4X
			MAX-ACCESS read-write
			STATUS current
			DESCRIPTION
				"AFD code"
		::= { hop3147c02v1Entry 107 }

		-- 1.3.6.1.4.1.10106.3.101291.1.1.109
		hop3147c02v1AncInsL1En OBJECT-TYPE
			SYNTAX Bit0No1Yes
			MAX-ACCESS read-write
			STATUS current
			DESCRIPTION
				"Enables ancillary packet insertion in line 1"
		::= { hop3147c02v1Entry 109 }

		-- 1.3.6.1.4.1.10106.3.101291.1.1.111
		hop3147c02v1AncInsL2En OBJECT-TYPE
			SYNTAX Bit0No1Yes
			MAX-ACCESS read-write
			STATUS current
			DESCRIPTION
				"Enables ancillary packet insertion in line 2"
		::= { hop3147c02v1Entry 111 }

		-- 1.3.6.1.4.1.10106.3.101291.1.1.113
		hop3147c02v1AncInsActVid OBJECT-TYPE
			SYNTAX Bit0Hrz1Av
			MAX-ACCESS read-write
			STATUS current
			DESCRIPTION
				"Enables selection between active video or horizontal blanking for packet insertion"
		::= { hop3147c02v1Entry 113 }

		-- 1.3.6.1.4.1.10106.3.101291.1.1.115
		hop3147c02v1AncInsLumNCr OBJECT-TYPE
			SYNTAX Bit0Chr1Lum
			MAX-ACCESS read-write
			STATUS current
			DESCRIPTION
				"Selects insertion in luminace/chrominance (HD/3G only)"
		::= { hop3147c02v1Entry 115 }

		-- 1.3.6.1.4.1.10106.3.101291.1.1.117
		hop3147c02v1AncInsPckNum OBJECT-TYPE
			SYNTAX Uint3
			MAX-ACCESS read-write
			STATUS current
			DESCRIPTION
				"ANC packet selecction between those stored in the memory"
		::= { hop3147c02v1Entry 117 }

		-- 1.3.6.1.4.1.10106.3.101291.1.1.119
		hop3147c02v1AncInsL1 OBJECT-TYPE
			SYNTAX Uint11
			MAX-ACCESS read-write
			STATUS current
			DESCRIPTION
				"Insertion line L1 where the first packet will be inserted."
		::= { hop3147c02v1Entry 119 }

		-- 1.3.6.1.4.1.10106.3.101291.1.1.121
		hop3147c02v1AncInsL2 OBJECT-TYPE
			SYNTAX Uint11
			MAX-ACCESS read-write
			STATUS current
			DESCRIPTION
				"Insertion line L2 where the second packet will be inserted."
		::= { hop3147c02v1Entry 121 }

		-- 1.3.6.1.4.1.10106.3.101291.1.1.123
		hop3147c02v1AncInsRepet OBJECT-TYPE
			SYNTAX AncInserterRep
			MAX-ACCESS read-write
			STATUS current
			DESCRIPTION
				"Number of frames for insertion. The value 0 means continuous insertion"
		::= { hop3147c02v1Entry 123 }

		-- 1.3.6.1.4.1.10106.3.101291.1.1.125
		hop3147c02v1GpisInvPrst1 OBJECT-TYPE
			SYNTAX Bit0No1Yes
			MAX-ACCESS read-write
			STATUS current
			DESCRIPTION
				"Enables preset restoring using GPI1"
		::= { hop3147c02v1Entry 125 }

		-- 1.3.6.1.4.1.10106.3.101291.1.1.127
		hop3147c02v1GpisInvPrst2 OBJECT-TYPE
			SYNTAX Bit0No1Yes
			MAX-ACCESS read-write
			STATUS current
			DESCRIPTION
				"Enables preset restoring using GPI1"
		::= { hop3147c02v1Entry 127 }

		-- 1.3.6.1.4.1.10106.3.101291.1.1.129
		hop3147c02v1GpisInvPrst3 OBJECT-TYPE
			SYNTAX Bit0No1Yes
			MAX-ACCESS read-write
			STATUS current
			DESCRIPTION
				"Enables preset restoring using GPI1"
		::= { hop3147c02v1Entry 129 }

		-- 1.3.6.1.4.1.10106.3.101291.1.1.131
		hop3147c02v1GpisInvPrst4 OBJECT-TYPE
			SYNTAX Bit0No1Yes
			MAX-ACCESS read-write
			STATUS current
			DESCRIPTION
				"Enables preset restoring using GPI4"
		::= { hop3147c02v1Entry 131 }

		-- 1.3.6.1.4.1.10106.3.101291.1.1.133
		hop3147c02v1GpisInvPrst5 OBJECT-TYPE
			SYNTAX Bit0No1Yes
			MAX-ACCESS read-write
			STATUS current
			DESCRIPTION
				"Enables preset restoring using GPI5"
		::= { hop3147c02v1Entry 133 }

		-- 1.3.6.1.4.1.10106.3.101291.1.1.135
		hop3147c02v1GpisInvPrst6 OBJECT-TYPE
			SYNTAX Bit0No1Yes
			MAX-ACCESS read-write
			STATUS current
			DESCRIPTION
				"Enables preset restoring using GPI6"
		::= { hop3147c02v1Entry 135 }

		-- 1.3.6.1.4.1.10106.3.101291.1.1.137
		hop3147c02v1GpisInvPrst7 OBJECT-TYPE
			SYNTAX Bit0No1Yes
			MAX-ACCESS read-write
			STATUS current
			DESCRIPTION
				"Enables preset restoring using GPI7"
		::= { hop3147c02v1Entry 137 }

		-- 1.3.6.1.4.1.10106.3.101291.1.1.139
		hop3147c02v1GpisInvPrst8 OBJECT-TYPE
			SYNTAX Bit0No1Yes
			MAX-ACCESS read-write
			STATUS current
			DESCRIPTION
				"Enables preset restoring using GPI8"
		::= { hop3147c02v1Entry 139 }

		-- 1.3.6.1.4.1.10106.3.101291.1.1.141
		hop3147c02v1TxtBridgeEn0 OBJECT-TYPE
			SYNTAX Bit0No1Yes
			MAX-ACCESS read-write
			STATUS current
			DESCRIPTION
				"Line 0 insertion enable"
		::= { hop3147c02v1Entry 141 }

		-- 1.3.6.1.4.1.10106.3.101291.1.1.143
		hop3147c02v1TxtBridgeEn1 OBJECT-TYPE
			SYNTAX Bit0No1Yes
			MAX-ACCESS read-write
			STATUS current
			DESCRIPTION
				"Line 1 insertion enable"
		::= { hop3147c02v1Entry 143 }

		-- 1.3.6.1.4.1.10106.3.101291.1.1.145
		hop3147c02v1TxtBridgeEn2 OBJECT-TYPE
			SYNTAX Bit0No1Yes
			MAX-ACCESS read-write
			STATUS current
			DESCRIPTION
				"Line 2 insertion enable"
		::= { hop3147c02v1Entry 145 }

		-- 1.3.6.1.4.1.10106.3.101291.1.1.147
		hop3147c02v1TxtBridgeEn3 OBJECT-TYPE
			SYNTAX Bit0No1Yes
			MAX-ACCESS read-write
			STATUS current
			DESCRIPTION
				"Line 3 insertion enable"
		::= { hop3147c02v1Entry 147 }

		-- 1.3.6.1.4.1.10106.3.101291.1.1.149
		hop3147c02v1TxtBridgeEn4 OBJECT-TYPE
			SYNTAX Bit0No1Yes
			MAX-ACCESS read-write
			STATUS current
			DESCRIPTION
				"Line 4 insertion enable"
		::= { hop3147c02v1Entry 149 }

		-- 1.3.6.1.4.1.10106.3.101291.1.1.151
		hop3147c02v1TxtBridgeEn5 OBJECT-TYPE
			SYNTAX Bit0No1Yes
			MAX-ACCESS read-write
			STATUS current
			DESCRIPTION
				"Line 5 insertion enable"
		::= { hop3147c02v1Entry 151 }

		-- 1.3.6.1.4.1.10106.3.101291.1.1.153
		hop3147c02v1TxtBridgeEn6 OBJECT-TYPE
			SYNTAX Bit0No1Yes
			MAX-ACCESS read-write
			STATUS current
			DESCRIPTION
				"Line 6 insertion enable"
		::= { hop3147c02v1Entry 153 }

		-- 1.3.6.1.4.1.10106.3.101291.1.1.155
		hop3147c02v1TxtBridgeEn7 OBJECT-TYPE
			SYNTAX Bit0No1Yes
			MAX-ACCESS read-write
			STATUS current
			DESCRIPTION
				"Line 7 insertion enable"
		::= { hop3147c02v1Entry 155 }

		-- 1.3.6.1.4.1.10106.3.101291.1.1.157
		hop3147c02v1TxtBridgeEn8 OBJECT-TYPE
			SYNTAX Bit0No1Yes
			MAX-ACCESS read-write
			STATUS current
			DESCRIPTION
				"Line 8 insertion enable"
		::= { hop3147c02v1Entry 157 }

		-- 1.3.6.1.4.1.10106.3.101291.1.1.159
		hop3147c02v1TxtBridgeEn9 OBJECT-TYPE
			SYNTAX Bit0No1Yes
			MAX-ACCESS read-write
			STATUS current
			DESCRIPTION
				"Line 9 insertion enable"
		::= { hop3147c02v1Entry 159 }

		-- 1.3.6.1.4.1.10106.3.101291.1.1.161
		hop3147c02v1TxtBridgeEn10 OBJECT-TYPE
			SYNTAX Bit0No1Yes
			MAX-ACCESS read-write
			STATUS current
			DESCRIPTION
				"Line 10 insertion enable"
		::= { hop3147c02v1Entry 161 }

		-- 1.3.6.1.4.1.10106.3.101291.1.1.163
		hop3147c02v1TxtBridgeEn11 OBJECT-TYPE
			SYNTAX Bit0No1Yes
			MAX-ACCESS read-write
			STATUS current
			DESCRIPTION
				"Line 11 insertion enable"
		::= { hop3147c02v1Entry 163 }

		-- 1.3.6.1.4.1.10106.3.101291.1.1.165
		hop3147c02v1TxtBridgeEn12 OBJECT-TYPE
			SYNTAX Bit0No1Yes
			MAX-ACCESS read-write
			STATUS current
			DESCRIPTION
				"Line 12 insertion enable"
		::= { hop3147c02v1Entry 165 }

		-- 1.3.6.1.4.1.10106.3.101291.1.1.167
		hop3147c02v1TxtBridgeEn13 OBJECT-TYPE
			SYNTAX Bit0No1Yes
			MAX-ACCESS read-write
			STATUS current
			DESCRIPTION
				"Line 13 insertion enable"
		::= { hop3147c02v1Entry 167 }

		-- 1.3.6.1.4.1.10106.3.101291.1.1.169
		hop3147c02v1TxtBridgeEn14 OBJECT-TYPE
			SYNTAX Bit0No1Yes
			MAX-ACCESS read-write
			STATUS current
			DESCRIPTION
				"Line 14 insertion enable"
		::= { hop3147c02v1Entry 169 }

		-- 1.3.6.1.4.1.10106.3.101291.1.1.171
		hop3147c02v1TxtBridgeEn15 OBJECT-TYPE
			SYNTAX Bit0No1Yes
			MAX-ACCESS read-write
			STATUS current
			DESCRIPTION
				"Line 15 insertion enable"
		::= { hop3147c02v1Entry 171 }

		-- 1.3.6.1.4.1.10106.3.101291.1.1.173
		hop3147c02v1TxtBridgeEn16 OBJECT-TYPE
			SYNTAX Bit0No1Yes
			MAX-ACCESS read-write
			STATUS current
			DESCRIPTION
				"Line 16 insertion enable"
		::= { hop3147c02v1Entry 173 }

		-- 1.3.6.1.4.1.10106.3.101291.1.1.175
		hop3147c02v1TxtBridgeEn17 OBJECT-TYPE
			SYNTAX Bit0No1Yes
			MAX-ACCESS read-write
			STATUS current
			DESCRIPTION
				"Line 17 insertion enable"
		::= { hop3147c02v1Entry 175 }

		-- 1.3.6.1.4.1.10106.3.101291.1.1.177
		hop3147c02v1TxtBridgeEn18 OBJECT-TYPE
			SYNTAX Bit0No1Yes
			MAX-ACCESS read-write
			STATUS current
			DESCRIPTION
				"Line 18 insertion enable"
		::= { hop3147c02v1Entry 177 }

		-- 1.3.6.1.4.1.10106.3.101291.1.1.179
		hop3147c02v1TxtBridgeEn19 OBJECT-TYPE
			SYNTAX Bit0No1Yes
			MAX-ACCESS read-write
			STATUS current
			DESCRIPTION
				"Line 19 insertion enable"
		::= { hop3147c02v1Entry 179 }

		-- 1.3.6.1.4.1.10106.3.101291.1.1.181
		hop3147c02v1TxtBridgeEn20 OBJECT-TYPE
			SYNTAX Bit0No1Yes
			MAX-ACCESS read-write
			STATUS current
			DESCRIPTION
				"Line 20 insertion enable"
		::= { hop3147c02v1Entry 181 }

		-- 1.3.6.1.4.1.10106.3.101291.1.1.183
		hop3147c02v1TxtBridgeEn21 OBJECT-TYPE
			SYNTAX Bit0No1Yes
			MAX-ACCESS read-write
			STATUS current
			DESCRIPTION
				"Line 21 insertion enable"
		::= { hop3147c02v1Entry 183 }

		-- 1.3.6.1.4.1.10106.3.101291.1.1.185
		hop3147c02v1TxtBridgeEn22 OBJECT-TYPE
			SYNTAX Bit0No1Yes
			MAX-ACCESS read-write
			STATUS current
			DESCRIPTION
				"Line 22 insertion enable"
		::= { hop3147c02v1Entry 185 }

		-- 1.3.6.1.4.1.10106.3.101291.1.1.187
		hop3147c02v1TxtBridgeEn23 OBJECT-TYPE
			SYNTAX Bit0No1Yes
			MAX-ACCESS read-write
			STATUS current
			DESCRIPTION
				"Line 23 insertion enable"
		::= { hop3147c02v1Entry 187 }

		-- 1.3.6.1.4.1.10106.3.101291.1.1.189
		hop3147c02v1TxtBridgeEn24 OBJECT-TYPE
			SYNTAX Bit0No1Yes
			MAX-ACCESS read-write
			STATUS current
			DESCRIPTION
				"Line 24 insertion enable"
		::= { hop3147c02v1Entry 189 }

		-- 1.3.6.1.4.1.10106.3.101291.1.1.191
		hop3147c02v1TxtBridgeEn25 OBJECT-TYPE
			SYNTAX Bit0No1Yes
			MAX-ACCESS read-write
			STATUS current
			DESCRIPTION
				"Line 25 insertion enable"
		::= { hop3147c02v1Entry 191 }

		-- 1.3.6.1.4.1.10106.3.101291.1.1.193
		hop3147c02v1TxtBridgeEn26 OBJECT-TYPE
			SYNTAX Bit0No1Yes
			MAX-ACCESS read-write
			STATUS current
			DESCRIPTION
				"Line 26 insertion enable"
		::= { hop3147c02v1Entry 193 }

		-- 1.3.6.1.4.1.10106.3.101291.1.1.195
		hop3147c02v1TxtBridgeEn27 OBJECT-TYPE
			SYNTAX Bit0No1Yes
			MAX-ACCESS read-write
			STATUS current
			DESCRIPTION
				"Line 27 insertion enable"
		::= { hop3147c02v1Entry 195 }

		-- 1.3.6.1.4.1.10106.3.101291.1.1.197
		hop3147c02v1TxtBridgeEn28 OBJECT-TYPE
			SYNTAX Bit0No1Yes
			MAX-ACCESS read-write
			STATUS current
			DESCRIPTION
				"Line 28 insertion enable"
		::= { hop3147c02v1Entry 197 }

		-- 1.3.6.1.4.1.10106.3.101291.1.1.199
		hop3147c02v1TxtBridgeEn29 OBJECT-TYPE
			SYNTAX Bit0No1Yes
			MAX-ACCESS read-write
			STATUS current
			DESCRIPTION
				"Line 29 insertion enable"
		::= { hop3147c02v1Entry 199 }

		-- 1.3.6.1.4.1.10106.3.101291.1.1.201
		hop3147c02v1TxtBridgeEn30 OBJECT-TYPE
			SYNTAX Bit0No1Yes
			MAX-ACCESS read-write
			STATUS current
			DESCRIPTION
				"Line 30 insertion enable"
		::= { hop3147c02v1Entry 201 }

		-- 1.3.6.1.4.1.10106.3.101291.1.1.203
		hop3147c02v1TxtBridgeEn31 OBJECT-TYPE
			SYNTAX Bit0No1Yes
			MAX-ACCESS read-write
			STATUS current
			DESCRIPTION
				"Line 31 insertion enable"
		::= { hop3147c02v1Entry 203 }

		-- 1.3.6.1.4.1.10106.3.101291.1.1.205
		hop3147c02v1TxtBridge0 OBJECT-TYPE
			SYNTAX TxtBridgeLine
			MAX-ACCESS read-write
			STATUS current
			DESCRIPTION
				"Line 0 insertion source"
		::= { hop3147c02v1Entry 205 }

		-- 1.3.6.1.4.1.10106.3.101291.1.1.207
		hop3147c02v1TxtBridge1 OBJECT-TYPE
			SYNTAX TxtBridgeLine
			MAX-ACCESS read-write
			STATUS current
			DESCRIPTION
				"Line 1 insertion source"
		::= { hop3147c02v1Entry 207 }

		-- 1.3.6.1.4.1.10106.3.101291.1.1.209
		hop3147c02v1TxtBridge2 OBJECT-TYPE
			SYNTAX TxtBridgeLine
			MAX-ACCESS read-write
			STATUS current
			DESCRIPTION
				"Line 2 insertion source"
		::= { hop3147c02v1Entry 209 }

		-- 1.3.6.1.4.1.10106.3.101291.1.1.211
		hop3147c02v1TxtBridge3 OBJECT-TYPE
			SYNTAX TxtBridgeLine
			MAX-ACCESS read-write
			STATUS current
			DESCRIPTION
				"Line 3 insertion source"
		::= { hop3147c02v1Entry 211 }

		-- 1.3.6.1.4.1.10106.3.101291.1.1.213
		hop3147c02v1TxtBridge4 OBJECT-TYPE
			SYNTAX TxtBridgeLine
			MAX-ACCESS read-write
			STATUS current
			DESCRIPTION
				"Line 4 insertion source"
		::= { hop3147c02v1Entry 213 }

		-- 1.3.6.1.4.1.10106.3.101291.1.1.215
		hop3147c02v1TxtBridge5 OBJECT-TYPE
			SYNTAX TxtBridgeLine
			MAX-ACCESS read-write
			STATUS current
			DESCRIPTION
				"Line 5 insertion source"
		::= { hop3147c02v1Entry 215 }

		-- 1.3.6.1.4.1.10106.3.101291.1.1.217
		hop3147c02v1TxtBridge6 OBJECT-TYPE
			SYNTAX TxtBridgeLine
			MAX-ACCESS read-write
			STATUS current
			DESCRIPTION
				"Line 6 insertion source"
		::= { hop3147c02v1Entry 217 }

		-- 1.3.6.1.4.1.10106.3.101291.1.1.219
		hop3147c02v1TxtBridge7 OBJECT-TYPE
			SYNTAX TxtBridgeLine
			MAX-ACCESS read-write
			STATUS current
			DESCRIPTION
				"Line 7 insertion source"
		::= { hop3147c02v1Entry 219 }

		-- 1.3.6.1.4.1.10106.3.101291.1.1.221
		hop3147c02v1TxtBridge8 OBJECT-TYPE
			SYNTAX TxtBridgeLine
			MAX-ACCESS read-write
			STATUS current
			DESCRIPTION
				"Line 8 insertion source"
		::= { hop3147c02v1Entry 221 }

		-- 1.3.6.1.4.1.10106.3.101291.1.1.223
		hop3147c02v1TxtBridge9 OBJECT-TYPE
			SYNTAX TxtBridgeLine
			MAX-ACCESS read-write
			STATUS current
			DESCRIPTION
				"Line 9 insertion source"
		::= { hop3147c02v1Entry 223 }

		-- 1.3.6.1.4.1.10106.3.101291.1.1.225
		hop3147c02v1TxtBridge10 OBJECT-TYPE
			SYNTAX TxtBridgeLine
			MAX-ACCESS read-write
			STATUS current
			DESCRIPTION
				"Line 10 insertion source"
		::= { hop3147c02v1Entry 225 }

		-- 1.3.6.1.4.1.10106.3.101291.1.1.227
		hop3147c02v1TxtBridge11 OBJECT-TYPE
			SYNTAX TxtBridgeLine
			MAX-ACCESS read-write
			STATUS current
			DESCRIPTION
				"Line 11 insertion source"
		::= { hop3147c02v1Entry 227 }

		-- 1.3.6.1.4.1.10106.3.101291.1.1.229
		hop3147c02v1TxtBridge12 OBJECT-TYPE
			SYNTAX TxtBridgeLine
			MAX-ACCESS read-write
			STATUS current
			DESCRIPTION
				"Line 12 insertion source"
		::= { hop3147c02v1Entry 229 }

		-- 1.3.6.1.4.1.10106.3.101291.1.1.231
		hop3147c02v1TxtBridge13 OBJECT-TYPE
			SYNTAX TxtBridgeLine
			MAX-ACCESS read-write
			STATUS current
			DESCRIPTION
				"Line 13 insertion source"
		::= { hop3147c02v1Entry 231 }

		-- 1.3.6.1.4.1.10106.3.101291.1.1.233
		hop3147c02v1TxtBridge14 OBJECT-TYPE
			SYNTAX TxtBridgeLine
			MAX-ACCESS read-write
			STATUS current
			DESCRIPTION
				"Line 14 insertion source"
		::= { hop3147c02v1Entry 233 }

		-- 1.3.6.1.4.1.10106.3.101291.1.1.235
		hop3147c02v1TxtBridge15 OBJECT-TYPE
			SYNTAX TxtBridgeLine
			MAX-ACCESS read-write
			STATUS current
			DESCRIPTION
				"Line 15 insertion source"
		::= { hop3147c02v1Entry 235 }

		-- 1.3.6.1.4.1.10106.3.101291.1.1.237
		hop3147c02v1TxtBridge16 OBJECT-TYPE
			SYNTAX TxtBridgeLine
			MAX-ACCESS read-write
			STATUS current
			DESCRIPTION
				"Line 16 insertion source"
		::= { hop3147c02v1Entry 237 }

		-- 1.3.6.1.4.1.10106.3.101291.1.1.239
		hop3147c02v1TxtBridge17 OBJECT-TYPE
			SYNTAX TxtBridgeLine
			MAX-ACCESS read-write
			STATUS current
			DESCRIPTION
				"Line 17 insertion source"
		::= { hop3147c02v1Entry 239 }

		-- 1.3.6.1.4.1.10106.3.101291.1.1.241
		hop3147c02v1TxtBridge18 OBJECT-TYPE
			SYNTAX TxtBridgeLine
			MAX-ACCESS read-write
			STATUS current
			DESCRIPTION
				"Line 18 insertion source"
		::= { hop3147c02v1Entry 241 }

		-- 1.3.6.1.4.1.10106.3.101291.1.1.243
		hop3147c02v1TxtBridge19 OBJECT-TYPE
			SYNTAX TxtBridgeLine
			MAX-ACCESS read-write
			STATUS current
			DESCRIPTION
				"Line 19 insertion source"
		::= { hop3147c02v1Entry 243 }

		-- 1.3.6.1.4.1.10106.3.101291.1.1.245
		hop3147c02v1TxtBridge20 OBJECT-TYPE
			SYNTAX TxtBridgeLine
			MAX-ACCESS read-write
			STATUS current
			DESCRIPTION
				"Line 20 insertion source"
		::= { hop3147c02v1Entry 245 }

		-- 1.3.6.1.4.1.10106.3.101291.1.1.247
		hop3147c02v1TxtBridge21 OBJECT-TYPE
			SYNTAX TxtBridgeLine
			MAX-ACCESS read-write
			STATUS current
			DESCRIPTION
				"Line 21 insertion source"
		::= { hop3147c02v1Entry 247 }

		-- 1.3.6.1.4.1.10106.3.101291.1.1.249
		hop3147c02v1TxtBridge22 OBJECT-TYPE
			SYNTAX TxtBridgeLine
			MAX-ACCESS read-write
			STATUS current
			DESCRIPTION
				"Line 22 insertion source"
		::= { hop3147c02v1Entry 249 }

		-- 1.3.6.1.4.1.10106.3.101291.1.1.251
		hop3147c02v1TxtBridge23 OBJECT-TYPE
			SYNTAX TxtBridgeLine
			MAX-ACCESS read-write
			STATUS current
			DESCRIPTION
				"Line 23 insertion source"
		::= { hop3147c02v1Entry 251 }

		-- 1.3.6.1.4.1.10106.3.101291.1.1.253
		hop3147c02v1TxtBridge24 OBJECT-TYPE
			SYNTAX TxtBridgeLine
			MAX-ACCESS read-write
			STATUS current
			DESCRIPTION
				"Line 24 insertion source"
		::= { hop3147c02v1Entry 253 }

		-- 1.3.6.1.4.1.10106.3.101291.1.1.255
		hop3147c02v1TxtBridge25 OBJECT-TYPE
			SYNTAX TxtBridgeLine
			MAX-ACCESS read-write
			STATUS current
			DESCRIPTION
				"Line 25 insertion source"
		::= { hop3147c02v1Entry 255 }

		-- 1.3.6.1.4.1.10106.3.101291.1.1.257
		hop3147c02v1TxtBridge26 OBJECT-TYPE
			SYNTAX TxtBridgeLine
			MAX-ACCESS read-write
			STATUS current
			DESCRIPTION
				"Line 26 insertion source"
		::= { hop3147c02v1Entry 257 }

		-- 1.3.6.1.4.1.10106.3.101291.1.1.259
		hop3147c02v1TxtBridge27 OBJECT-TYPE
			SYNTAX TxtBridgeLine
			MAX-ACCESS read-write
			STATUS current
			DESCRIPTION
				"Line 27 insertion source"
		::= { hop3147c02v1Entry 259 }

		-- 1.3.6.1.4.1.10106.3.101291.1.1.261
		hop3147c02v1TxtBridge28 OBJECT-TYPE
			SYNTAX TxtBridgeLine
			MAX-ACCESS read-write
			STATUS current
			DESCRIPTION
				"Line 28 insertion source"
		::= { hop3147c02v1Entry 261 }

		-- 1.3.6.1.4.1.10106.3.101291.1.1.263
		hop3147c02v1TxtBridge29 OBJECT-TYPE
			SYNTAX TxtBridgeLine
			MAX-ACCESS read-write
			STATUS current
			DESCRIPTION
				"Line 29 insertion source"
		::= { hop3147c02v1Entry 263 }

		-- 1.3.6.1.4.1.10106.3.101291.1.1.265
		hop3147c02v1TxtBridge30 OBJECT-TYPE
			SYNTAX TxtBridgeLine
			MAX-ACCESS read-write
			STATUS current
			DESCRIPTION
				"Line 30 insertion source"
		::= { hop3147c02v1Entry 265 }

		-- 1.3.6.1.4.1.10106.3.101291.1.1.267
		hop3147c02v1TxtBridge31 OBJECT-TYPE
			SYNTAX TxtBridgeLine
			MAX-ACCESS read-write
			STATUS current
			DESCRIPTION
				"Line 31 insertion source"
		::= { hop3147c02v1Entry 267 }

		-- 1.3.6.1.4.1.10106.3.101291.1.1.269
		hop3147c02v1TxtBridgeOp47 OBJECT-TYPE
			SYNTAX Uint8
			MAX-ACCESS read-write
			STATUS current
			DESCRIPTION
				"First line for OP47 packet insertion when HD/3G"
		::= { hop3147c02v1Entry 269 }

		-- 1.3.6.1.4.1.10106.3.101291.1.1.271
		hop3147c02v1TxtFail OBJECT-TYPE
			SYNTAX BitFail
			MAX-ACCESS read-only
			STATUS current
			DESCRIPTION
				"Teletext signal not found"
		::= { hop3147c02v1Entry 271 }

		-- 1.3.6.1.4.1.10106.3.101291.1.1.272
		hop3147c02v1TxtFailTrapEnable OBJECT-TYPE
			SYNTAX AlarmEnable
			MAX-ACCESS read-write
			STATUS current
			DESCRIPTION
				"Teletext signal not found Trap Enable"
		::= { hop3147c02v1Entry 272 }

		-- 1.3.6.1.4.1.10106.3.101291.1.1.273
		hop3147c02v1TxtInsFail OBJECT-TYPE
			SYNTAX BitFail
			MAX-ACCESS read-only
			STATUS current
			DESCRIPTION
				"OP47 packet can not be inserted"
		::= { hop3147c02v1Entry 273 }

		-- 1.3.6.1.4.1.10106.3.101291.1.1.274
		hop3147c02v1TxtInsFailTrapEnable OBJECT-TYPE
			SYNTAX AlarmEnable
			MAX-ACCESS read-write
			STATUS current
			DESCRIPTION
				"OP47 packet can not be inserted Trap Enable"
		::= { hop3147c02v1Entry 274 }

		-- 1.3.6.1.4.1.10106.3.101291.1.1.275
		hop3147c02v1AudioFail OBJECT-TYPE
			SYNTAX BitFail
			MAX-ACCESS read-only
			STATUS current
			DESCRIPTION
				"Audio presence fail"
		::= { hop3147c02v1Entry 275 }

		-- 1.3.6.1.4.1.10106.3.101291.1.1.276
		hop3147c02v1AudioFailTrapEnable OBJECT-TYPE
			SYNTAX AlarmEnable
			MAX-ACCESS read-write
			STATUS current
			DESCRIPTION
				"Audio presence fail Trap Enable"
		::= { hop3147c02v1Entry 276 }

		-- 1.3.6.1.4.1.10106.3.101291.1.1.277
		hop3147c02v1AudioInsFail OBJECT-TYPE
			SYNTAX BitFail
			MAX-ACCESS read-only
			STATUS current
			DESCRIPTION
				"Audio insertion fail"
		::= { hop3147c02v1Entry 277 }

		-- 1.3.6.1.4.1.10106.3.101291.1.1.278
		hop3147c02v1AudioInsFailTrapEnable OBJECT-TYPE
			SYNTAX AlarmEnable
			MAX-ACCESS read-write
			STATUS current
			DESCRIPTION
				"Audio insertion fail Trap Enable"
		::= { hop3147c02v1Entry 278 }

		-- 1.3.6.1.4.1.10106.3.101291.1.1.279
		hop3147c02v1ViiInsFail OBJECT-TYPE
			SYNTAX BitFail
			MAX-ACCESS read-only
			STATUS current
			DESCRIPTION
				"VII insertion fail"
		::= { hop3147c02v1Entry 279 }

		-- 1.3.6.1.4.1.10106.3.101291.1.1.280
		hop3147c02v1ViiInsFailTrapEnable OBJECT-TYPE
			SYNTAX AlarmEnable
			MAX-ACCESS read-write
			STATUS current
			DESCRIPTION
				"VII insertion fail Trap Enable"
		::= { hop3147c02v1Entry 280 }

		-- 1.3.6.1.4.1.10106.3.101291.1.1.281
		hop3147c02v1WssInsFail OBJECT-TYPE
			SYNTAX BitFail
			MAX-ACCESS read-only
			STATUS current
			DESCRIPTION
				"WSS insertion fail"
		::= { hop3147c02v1Entry 281 }

		-- 1.3.6.1.4.1.10106.3.101291.1.1.282
		hop3147c02v1WssInsFailTrapEnable OBJECT-TYPE
			SYNTAX AlarmEnable
			MAX-ACCESS read-write
			STATUS current
			DESCRIPTION
				"WSS insertion fail Trap Enable"
		::= { hop3147c02v1Entry 282 }

		-- 1.3.6.1.4.1.10106.3.101291.1.1.283
		hop3147c02v1AfdInsFail OBJECT-TYPE
			SYNTAX BitFail
			MAX-ACCESS read-only
			STATUS current
			DESCRIPTION
				"AFD  (SMPTE 2016-3) insertion fail"
		::= { hop3147c02v1Entry 283 }

		-- 1.3.6.1.4.1.10106.3.101291.1.1.284
		hop3147c02v1AfdInsFailTrapEnable OBJECT-TYPE
			SYNTAX AlarmEnable
			MAX-ACCESS read-write
			STATUS current
			DESCRIPTION
				"AFD  (SMPTE 2016-3) insertion fail Trap Enable"
		::= { hop3147c02v1Entry 284 }

		-- 1.3.6.1.4.1.10106.3.101291.1.1.285
		hop3147c02v1NoSignal0 OBJECT-TYPE
			SYNTAX BitFail
			MAX-ACCESS read-only
			STATUS current
			DESCRIPTION
				"There is no SDI signal or the format is not supported MAIN INPUT"
		::= { hop3147c02v1Entry 285 }

		-- 1.3.6.1.4.1.10106.3.101291.1.1.286
		hop3147c02v1NoSignal0TrapEnable OBJECT-TYPE
			SYNTAX AlarmEnable
			MAX-ACCESS read-write
			STATUS current
			DESCRIPTION
				"There is no SDI signal or the format is not supported MAIN INPUT Trap Enable"
		::= { hop3147c02v1Entry 286 }

		-- 1.3.6.1.4.1.10106.3.101291.1.1.287
		hop3147c02v1Unlocked0 OBJECT-TYPE
			SYNTAX BitFail
			MAX-ACCESS read-only
			STATUS current
			DESCRIPTION
				"Indicates signal unlock fail MAIN INPUT"
		::= { hop3147c02v1Entry 287 }

		-- 1.3.6.1.4.1.10106.3.101291.1.1.288
		hop3147c02v1Unlocked0TrapEnable OBJECT-TYPE
			SYNTAX AlarmEnable
			MAX-ACCESS read-write
			STATUS current
			DESCRIPTION
				"Indicates signal unlock fail MAIN INPUT Trap Enable"
		::= { hop3147c02v1Entry 288 }

		-- 1.3.6.1.4.1.10106.3.101291.1.1.289
		hop3147c02v1EdhCrc0 OBJECT-TYPE
			SYNTAX BitFail
			MAX-ACCESS read-only
			STATUS current
			DESCRIPTION
				"There are EDH/CRC errors on SDI signal MAIN INPUT"
		::= { hop3147c02v1Entry 289 }

		-- 1.3.6.1.4.1.10106.3.101291.1.1.290
		hop3147c02v1EdhCrc0TrapEnable OBJECT-TYPE
			SYNTAX AlarmEnable
			MAX-ACCESS read-write
			STATUS current
			DESCRIPTION
				"There are EDH/CRC errors on SDI signal MAIN INPUT Trap Enable"
		::= { hop3147c02v1Entry 290 }

		-- 1.3.6.1.4.1.10106.3.101291.1.1.291
		hop3147c02v1Format0 OBJECT-TYPE
			SYNTAX SdiHd3gFmt3
			MAX-ACCESS read-only
			STATUS current
			DESCRIPTION
				"Indicates the SDI received signal format MAIN INPUT"
		::= { hop3147c02v1Entry 291 }

		-- 1.3.6.1.4.1.10106.3.101291.1.1.293
		hop3147c02v1NoSignal1 OBJECT-TYPE
			SYNTAX BitFail
			MAX-ACCESS read-only
			STATUS current
			DESCRIPTION
				"There is no SDI signal or the format is not supported AUX INPUT"
		::= { hop3147c02v1Entry 293 }

		-- 1.3.6.1.4.1.10106.3.101291.1.1.294
		hop3147c02v1NoSignal1TrapEnable OBJECT-TYPE
			SYNTAX AlarmEnable
			MAX-ACCESS read-write
			STATUS current
			DESCRIPTION
				"There is no SDI signal or the format is not supported AUX INPUT Trap Enable"
		::= { hop3147c02v1Entry 294 }

		-- 1.3.6.1.4.1.10106.3.101291.1.1.295
		hop3147c02v1Unlocked1 OBJECT-TYPE
			SYNTAX BitFail
			MAX-ACCESS read-only
			STATUS current
			DESCRIPTION
				"Indicates signal unlock fail AUX INPUT"
		::= { hop3147c02v1Entry 295 }

		-- 1.3.6.1.4.1.10106.3.101291.1.1.296
		hop3147c02v1Unlocked1TrapEnable OBJECT-TYPE
			SYNTAX AlarmEnable
			MAX-ACCESS read-write
			STATUS current
			DESCRIPTION
				"Indicates signal unlock fail AUX INPUT Trap Enable"
		::= { hop3147c02v1Entry 296 }

		-- 1.3.6.1.4.1.10106.3.101291.1.1.297
		hop3147c02v1EdhCrc1 OBJECT-TYPE
			SYNTAX BitFail
			MAX-ACCESS read-only
			STATUS current
			DESCRIPTION
				"There are EDH/CRC errors on SDI signal AUX INPUT"
		::= { hop3147c02v1Entry 297 }

		-- 1.3.6.1.4.1.10106.3.101291.1.1.298
		hop3147c02v1EdhCrc1TrapEnable OBJECT-TYPE
			SYNTAX AlarmEnable
			MAX-ACCESS read-write
			STATUS current
			DESCRIPTION
				"There are EDH/CRC errors on SDI signal AUX INPUT Trap Enable"
		::= { hop3147c02v1Entry 298 }

		-- 1.3.6.1.4.1.10106.3.101291.1.1.299
		hop3147c02v1Format1 OBJECT-TYPE
			SYNTAX SdiHd3gFmt3
			MAX-ACCESS read-only
			STATUS current
			DESCRIPTION
				"Indicates the SDI received signal format AUX INPUT"
		::= { hop3147c02v1Entry 299 }

		-- 1.3.6.1.4.1.10106.3.101291.1.1.301
		hop3147c02v1Gpi1 OBJECT-TYPE
			SYNTAX Bit0Off1On
			MAX-ACCESS read-only
			STATUS current
			DESCRIPTION
				"Transmitted GPI1"
		::= { hop3147c02v1Entry 301 }

		-- 1.3.6.1.4.1.10106.3.101291.1.1.302
		hop3147c02v1Gpi1TrapEnable OBJECT-TYPE
			SYNTAX AlarmEnable
			MAX-ACCESS read-write
			STATUS current
			DESCRIPTION
				"Transmitted GPI1 Trap Enable"
		::= { hop3147c02v1Entry 302 }

		-- 1.3.6.1.4.1.10106.3.101291.1.1.303
		hop3147c02v1Gpi2 OBJECT-TYPE
			SYNTAX Bit0Off1On
			MAX-ACCESS read-only
			STATUS current
			DESCRIPTION
				"Transmitted GPI2"
		::= { hop3147c02v1Entry 303 }

		-- 1.3.6.1.4.1.10106.3.101291.1.1.304
		hop3147c02v1Gpi2TrapEnable OBJECT-TYPE
			SYNTAX AlarmEnable
			MAX-ACCESS read-write
			STATUS current
			DESCRIPTION
				"Transmitted GPI2 Trap Enable"
		::= { hop3147c02v1Entry 304 }

		-- 1.3.6.1.4.1.10106.3.101291.1.1.305
		hop3147c02v1Gpi3 OBJECT-TYPE
			SYNTAX Bit0Off1On
			MAX-ACCESS read-only
			STATUS current
			DESCRIPTION
				"Transmitted GPI3"
		::= { hop3147c02v1Entry 305 }

		-- 1.3.6.1.4.1.10106.3.101291.1.1.306
		hop3147c02v1Gpi3TrapEnable OBJECT-TYPE
			SYNTAX AlarmEnable
			MAX-ACCESS read-write
			STATUS current
			DESCRIPTION
				"Transmitted GPI3 Trap Enable"
		::= { hop3147c02v1Entry 306 }

		-- 1.3.6.1.4.1.10106.3.101291.1.1.307
		hop3147c02v1Gpi4 OBJECT-TYPE
			SYNTAX Bit0Off1On
			MAX-ACCESS read-only
			STATUS current
			DESCRIPTION
				"Transmitted GPI4"
		::= { hop3147c02v1Entry 307 }

		-- 1.3.6.1.4.1.10106.3.101291.1.1.308
		hop3147c02v1Gpi4TrapEnable OBJECT-TYPE
			SYNTAX AlarmEnable
			MAX-ACCESS read-write
			STATUS current
			DESCRIPTION
				"Transmitted GPI4 Trap Enable"
		::= { hop3147c02v1Entry 308 }

		-- 1.3.6.1.4.1.10106.3.101291.1.1.309
		hop3147c02v1Gpi5 OBJECT-TYPE
			SYNTAX Bit0Off1On
			MAX-ACCESS read-only
			STATUS current
			DESCRIPTION
				"Transmitted GPI5"
		::= { hop3147c02v1Entry 309 }

		-- 1.3.6.1.4.1.10106.3.101291.1.1.310
		hop3147c02v1Gpi5TrapEnable OBJECT-TYPE
			SYNTAX AlarmEnable
			MAX-ACCESS read-write
			STATUS current
			DESCRIPTION
				"Transmitted GPI5 Trap Enable"
		::= { hop3147c02v1Entry 310 }

		-- 1.3.6.1.4.1.10106.3.101291.1.1.311
		hop3147c02v1Gpi6 OBJECT-TYPE
			SYNTAX Bit0Off1On
			MAX-ACCESS read-only
			STATUS current
			DESCRIPTION
				"Transmitted GPI6"
		::= { hop3147c02v1Entry 311 }

		-- 1.3.6.1.4.1.10106.3.101291.1.1.312
		hop3147c02v1Gpi6TrapEnable OBJECT-TYPE
			SYNTAX AlarmEnable
			MAX-ACCESS read-write
			STATUS current
			DESCRIPTION
				"Transmitted GPI6 Trap Enable"
		::= { hop3147c02v1Entry 312 }

		-- 1.3.6.1.4.1.10106.3.101291.1.1.313
		hop3147c02v1Gpi7 OBJECT-TYPE
			SYNTAX Bit0Off1On
			MAX-ACCESS read-only
			STATUS current
			DESCRIPTION
				"Transmitted GPI7"
		::= { hop3147c02v1Entry 313 }

		-- 1.3.6.1.4.1.10106.3.101291.1.1.314
		hop3147c02v1Gpi7TrapEnable OBJECT-TYPE
			SYNTAX AlarmEnable
			MAX-ACCESS read-write
			STATUS current
			DESCRIPTION
				"Transmitted GPI7 Trap Enable"
		::= { hop3147c02v1Entry 314 }

		-- 1.3.6.1.4.1.10106.3.101291.1.1.315
		hop3147c02v1Gpi8 OBJECT-TYPE
			SYNTAX Bit0Off1On
			MAX-ACCESS read-only
			STATUS current
			DESCRIPTION
				"Transmitted GPI8"
		::= { hop3147c02v1Entry 315 }

		-- 1.3.6.1.4.1.10106.3.101291.1.1.316
		hop3147c02v1Gpi8TrapEnable OBJECT-TYPE
			SYNTAX AlarmEnable
			MAX-ACCESS read-write
			STATUS current
			DESCRIPTION
				"Transmitted GPI8 Trap Enable"
		::= { hop3147c02v1Entry 316 }

		-- 1.3.6.1.4.1.10106.3.101291.1.1.317
		hop3147c02v1Gpo1 OBJECT-TYPE
			SYNTAX Bit0Off1On
			MAX-ACCESS read-only
			STATUS current
			DESCRIPTION
				"Received GPO1"
		::= { hop3147c02v1Entry 317 }

		-- 1.3.6.1.4.1.10106.3.101291.1.1.318
		hop3147c02v1Gpo1TrapEnable OBJECT-TYPE
			SYNTAX AlarmEnable
			MAX-ACCESS read-write
			STATUS current
			DESCRIPTION
				"Received GPO1 Trap Enable"
		::= { hop3147c02v1Entry 318 }

		-- 1.3.6.1.4.1.10106.3.101291.1.1.319
		hop3147c02v1Gpo2 OBJECT-TYPE
			SYNTAX Bit0Off1On
			MAX-ACCESS read-only
			STATUS current
			DESCRIPTION
				"Received GPO2"
		::= { hop3147c02v1Entry 319 }

		-- 1.3.6.1.4.1.10106.3.101291.1.1.320
		hop3147c02v1Gpo2TrapEnable OBJECT-TYPE
			SYNTAX AlarmEnable
			MAX-ACCESS read-write
			STATUS current
			DESCRIPTION
				"Received GPO2 Trap Enable"
		::= { hop3147c02v1Entry 320 }

		-- 1.3.6.1.4.1.10106.3.101291.1.1.321
		hop3147c02v1Gpo3 OBJECT-TYPE
			SYNTAX Bit0Off1On
			MAX-ACCESS read-only
			STATUS current
			DESCRIPTION
				"Received GPO3"
		::= { hop3147c02v1Entry 321 }

		-- 1.3.6.1.4.1.10106.3.101291.1.1.322
		hop3147c02v1Gpo3TrapEnable OBJECT-TYPE
			SYNTAX AlarmEnable
			MAX-ACCESS read-write
			STATUS current
			DESCRIPTION
				"Received GPO3 Trap Enable"
		::= { hop3147c02v1Entry 322 }

		-- 1.3.6.1.4.1.10106.3.101291.1.1.323
		hop3147c02v1Gpo4 OBJECT-TYPE
			SYNTAX Bit0Off1On
			MAX-ACCESS read-only
			STATUS current
			DESCRIPTION
				"Received GPO4"
		::= { hop3147c02v1Entry 323 }

		-- 1.3.6.1.4.1.10106.3.101291.1.1.324
		hop3147c02v1Gpo4TrapEnable OBJECT-TYPE
			SYNTAX AlarmEnable
			MAX-ACCESS read-write
			STATUS current
			DESCRIPTION
				"Received GPO4 Trap Enable"
		::= { hop3147c02v1Entry 324 }

		-- 1.3.6.1.4.1.10106.3.101291.1.1.325
		hop3147c02v1Gpo5 OBJECT-TYPE
			SYNTAX Bit0Off1On
			MAX-ACCESS read-only
			STATUS current
			DESCRIPTION
				"Received GPO5"
		::= { hop3147c02v1Entry 325 }

		-- 1.3.6.1.4.1.10106.3.101291.1.1.326
		hop3147c02v1Gpo5TrapEnable OBJECT-TYPE
			SYNTAX AlarmEnable
			MAX-ACCESS read-write
			STATUS current
			DESCRIPTION
				"Received GPO5 Trap Enable"
		::= { hop3147c02v1Entry 326 }

		-- 1.3.6.1.4.1.10106.3.101291.1.1.327
		hop3147c02v1Gpo6 OBJECT-TYPE
			SYNTAX Bit0Off1On
			MAX-ACCESS read-only
			STATUS current
			DESCRIPTION
				"Received GPO6"
		::= { hop3147c02v1Entry 327 }

		-- 1.3.6.1.4.1.10106.3.101291.1.1.328
		hop3147c02v1Gpo6TrapEnable OBJECT-TYPE
			SYNTAX AlarmEnable
			MAX-ACCESS read-write
			STATUS current
			DESCRIPTION
				"Received GPO6 Trap Enable"
		::= { hop3147c02v1Entry 328 }

		-- 1.3.6.1.4.1.10106.3.101291.1.1.329
		hop3147c02v1Gpo7 OBJECT-TYPE
			SYNTAX Bit0Off1On
			MAX-ACCESS read-only
			STATUS current
			DESCRIPTION
				"Received GPO7"
		::= { hop3147c02v1Entry 329 }

		-- 1.3.6.1.4.1.10106.3.101291.1.1.330
		hop3147c02v1Gpo7TrapEnable OBJECT-TYPE
			SYNTAX AlarmEnable
			MAX-ACCESS read-write
			STATUS current
			DESCRIPTION
				"Received GPO7 Trap Enable"
		::= { hop3147c02v1Entry 330 }

		-- 1.3.6.1.4.1.10106.3.101291.1.1.331
		hop3147c02v1Gpo8 OBJECT-TYPE
			SYNTAX Bit0Off1On
			MAX-ACCESS read-only
			STATUS current
			DESCRIPTION
				"Received GPO8"
		::= { hop3147c02v1Entry 331 }

		-- 1.3.6.1.4.1.10106.3.101291.1.1.332
		hop3147c02v1Gpo8TrapEnable OBJECT-TYPE
			SYNTAX AlarmEnable
			MAX-ACCESS read-write
			STATUS current
			DESCRIPTION
				"Received GPO8 Trap Enable"
		::= { hop3147c02v1Entry 332 }

		-- 1.3.6.1.4.1.10106.3.101291.1.1.333
		hop3147c02v1VitcAtcPres OBJECT-TYPE
			SYNTAX BitFailN
			MAX-ACCESS read-only
			STATUS current
			DESCRIPTION
				"VITC-ATC presence in AUX input"
		::= { hop3147c02v1Entry 333 }

		-- 1.3.6.1.4.1.10106.3.101291.1.1.334
		hop3147c02v1VitcAtcPresTrapEnable OBJECT-TYPE
			SYNTAX AlarmEnable
			MAX-ACCESS read-write
			STATUS current
			DESCRIPTION
				"VITC-ATC presence in AUX input Trap Enable"
		::= { hop3147c02v1Entry 334 }

		-- 1.3.6.1.4.1.10106.3.101291.1.1.335
		hop3147c02v1TxtAuxPres OBJECT-TYPE
			SYNTAX BitFailN
			MAX-ACCESS read-only
			STATUS current
			DESCRIPTION
				"TXT presence in AUX input"
		::= { hop3147c02v1Entry 335 }

		-- 1.3.6.1.4.1.10106.3.101291.1.1.336
		hop3147c02v1TxtAuxPresTrapEnable OBJECT-TYPE
			SYNTAX AlarmEnable
			MAX-ACCESS read-write
			STATUS current
			DESCRIPTION
				"TXT presence in AUX input Trap Enable"
		::= { hop3147c02v1Entry 336 }

		-- 1.3.6.1.4.1.10106.3.101291.1.1.337
		hop3147c02v1TxtPres OBJECT-TYPE
			SYNTAX BitFailN
			MAX-ACCESS read-only
			STATUS current
			DESCRIPTION
				"Teletext presence"
		::= { hop3147c02v1Entry 337 }

		-- 1.3.6.1.4.1.10106.3.101291.1.1.338
		hop3147c02v1TxtPresTrapEnable OBJECT-TYPE
			SYNTAX AlarmEnable
			MAX-ACCESS read-write
			STATUS current
			DESCRIPTION
				"Teletext presence Trap Enable"
		::= { hop3147c02v1Entry 338 }

		-- 1.3.6.1.4.1.10106.3.101291.1.1.339
		hop3147c02v1AncInsL1Ok OBJECT-TYPE
			SYNTAX BitFail
			MAX-ACCESS read-only
			STATUS current
			DESCRIPTION
				"Ancillary packet insertion in line 1 fail"
		::= { hop3147c02v1Entry 339 }

		-- 1.3.6.1.4.1.10106.3.101291.1.1.341
		hop3147c02v1AncInsL2Ok OBJECT-TYPE
			SYNTAX BitFail
			MAX-ACCESS read-only
			STATUS current
			DESCRIPTION
				"Ancillary packet insertion in line 1 fail"
		::= { hop3147c02v1Entry 341 }

		-- 1.3.6.1.4.1.10106.3.101291.1.1.343
		hop3147c02v1SerialNo OBJECT-TYPE
			SYNTAX SerialNo
			MAX-ACCESS read-only
			STATUS current
			DESCRIPTION
				"Serial number"
		::= { hop3147c02v1Entry 343 }

		-- 1.3.6.1.4.1.10106.3.101291.1.1.345
		hop3147c02v1SplStartInmEn OBJECT-TYPE
			SYNTAX Bit0No1Yes
			MAX-ACCESS read-write
			STATUS current
			DESCRIPTION
				"Enables insertion of splice start inmediate SCTE104 packets"
		::= { hop3147c02v1Entry 345 }

		-- 1.3.6.1.4.1.10106.3.101291.1.1.347
		hop3147c02v1SplEndInmEn OBJECT-TYPE
			SYNTAX Bit0No1Yes
			MAX-ACCESS read-write
			STATUS current
			DESCRIPTION
				"Enables insertion of splice end inmediate SCTE104 packets"
		::= { hop3147c02v1Entry 347 }

		-- 1.3.6.1.4.1.10106.3.101291.1.1.349
		hop3147c02v1SplStartNorEn OBJECT-TYPE
			SYNTAX Bit0No1Yes
			MAX-ACCESS read-write
			STATUS current
			DESCRIPTION
				"Enables insertion of splice start normal SCTE104 packets"
		::= { hop3147c02v1Entry 349 }

		-- 1.3.6.1.4.1.10106.3.101291.1.1.351
		hop3147c02v1SplEndNorEn OBJECT-TYPE
			SYNTAX Bit0No1Yes
			MAX-ACCESS read-write
			STATUS current
			DESCRIPTION
				"Enables insertion of splice end normal SCTE104 packets"
		::= { hop3147c02v1Entry 351 }

		-- 1.3.6.1.4.1.10106.3.101291.1.1.353
		hop3147c02v1Scte104StNDyn OBJECT-TYPE
			SYNTAX Bit0No1Yes
			MAX-ACCESS read-write
			STATUS current
			DESCRIPTION
				"Enables selection of the field break duration (present in SCTE104 start packets) between the static value stored in EEPROM and the dynamic value which autoresets with every packet transmision"
		::= { hop3147c02v1Entry 353 }

		-- 1.3.6.1.4.1.10106.3.101291.1.1.355
		hop3147c02v1Scte104AretTx OBJECT-TYPE
			SYNTAX Bit0No1Yes
			MAX-ACCESS read-write
			STATUS current
			DESCRIPTION
				"Autoreturn flag used in SCTE104 start packets"
		::= { hop3147c02v1Entry 355 }

		-- 1.3.6.1.4.1.10106.3.101291.1.1.357
		hop3147c02v1Scte104RxAck OBJECT-TYPE
			SYNTAX Bit0No1Yes
			MAX-ACCESS read-write
			STATUS current
			DESCRIPTION
				"Packed received acknowledgement.  Resets status registers of SCTE104 recived packets."
		::= { hop3147c02v1Entry 357 }

		-- 1.3.6.1.4.1.10106.3.101291.1.1.359
		hop3147c02v1Scte104RxAsEn OBJECT-TYPE
			SYNTAX Bit0No1Yes
			MAX-ACCESS read-write
			STATUS current
			DESCRIPTION
				"Enables AS index filter"
		::= { hop3147c02v1Entry 359 }

		-- 1.3.6.1.4.1.10106.3.101291.1.1.361
		hop3147c02v1Scte104RxAsFi OBJECT-TYPE
			SYNTAX Uint8
			MAX-ACCESS read-write
			STATUS current
			DESCRIPTION
				"AS index value selected for reading"
		::= { hop3147c02v1Entry 361 }

		-- 1.3.6.1.4.1.10106.3.101291.1.1.363
		hop3147c02v1Scte104TxAsId OBJECT-TYPE
			SYNTAX Uint8
			MAX-ACCESS read-write
			STATUS current
			DESCRIPTION
				"AS index source identifier"
		::= { hop3147c02v1Entry 363 }

		-- 1.3.6.1.4.1.10106.3.101291.1.1.365
		hop3147c02v1Scte104Line OBJECT-TYPE
			SYNTAX Uint6
			MAX-ACCESS read-write
			STATUS current
			DESCRIPTION
				"Insertion line where the packet will be inserted."
		::= { hop3147c02v1Entry 365 }

		-- 1.3.6.1.4.1.10106.3.101291.1.1.367
		hop3147c02v1Scte104PreRoll OBJECT-TYPE
			SYNTAX PreRoll
			MAX-ACCESS read-write
			STATUS current
			DESCRIPTION
				"Pre roll field present in SCTE104 packts of type normal"
		::= { hop3147c02v1Entry 367 }

		-- 1.3.6.1.4.1.10106.3.101291.1.1.369
		hop3147c02v1Scte104TxBrkds OBJECT-TYPE
			SYNTAX BreakDuration
			MAX-ACCESS read-write
			STATUS current
			DESCRIPTION
				"Static break duration field present in SCTE104 packts of type start"
		::= { hop3147c02v1Entry 369 }

		-- 1.3.6.1.4.1.10106.3.101291.1.1.371
		hop3147c02v1Scte104TxBrkdd OBJECT-TYPE
			SYNTAX BreakDuration
			MAX-ACCESS read-write
			STATUS current
			DESCRIPTION
				"Dynamic break duration field present in SCTE104 packts of type start"
		::= { hop3147c02v1Entry 371 }

		-- 1.3.6.1.4.1.10106.3.101291.1.1.373
		hop3147c02v1Scte104InsF OBJECT-TYPE
			SYNTAX BitFail
			MAX-ACCESS read-only
			STATUS current
			DESCRIPTION
				"SCTE 104 packet insertion fail"
		::= { hop3147c02v1Entry 373 }

		-- 1.3.6.1.4.1.10106.3.101291.1.1.375
		hop3147c02v1Scte104RxF OBJECT-TYPE
			SYNTAX BitFail
			MAX-ACCESS read-only
			STATUS current
			DESCRIPTION
				"Packet fail. It shows when a packet has just been received and the message number is not consecutive to the previous one."
		::= { hop3147c02v1Entry 375 }

		-- 1.3.6.1.4.1.10106.3.101291.1.1.377
		hop3147c02v1Scte104Status OBJECT-TYPE
			SYNTAX Bit0Off1On
			MAX-ACCESS read-only
			STATUS current
			DESCRIPTION
				"Splice status according to the received packets. GPO1 will reflect its status when SCTE 104 GPO source mode is selected"
		::= { hop3147c02v1Entry 377 }

		-- 1.3.6.1.4.1.10106.3.101291.1.1.379
		hop3147c02v1Scte104AretRx OBJECT-TYPE
			SYNTAX Bit0Off1On
			MAX-ACCESS read-only
			STATUS current
			DESCRIPTION
				"Autoretun flag received"
		::= { hop3147c02v1Entry 379 }

		-- 1.3.6.1.4.1.10106.3.101291.1.1.381
		hop3147c02v1Scte104RxPck OBJECT-TYPE
			SYNTAX Scte104PckType
			MAX-ACCESS read-only
			STATUS current
			DESCRIPTION
				"Packet type received"
		::= { hop3147c02v1Entry 381 }

		-- 1.3.6.1.4.1.10106.3.101291.1.1.383
		hop3147c02v1Scte104RxAsId OBJECT-TYPE
			SYNTAX Uint8
			MAX-ACCESS read-only
			STATUS current
			DESCRIPTION
				"AS index of the received packet"
		::= { hop3147c02v1Entry 383 }

		-- 1.3.6.1.4.1.10106.3.101291.1.1.385
		hop3147c02v1Scte104RxPrRo OBJECT-TYPE
			SYNTAX PreRoll
			MAX-ACCESS read-only
			STATUS current
			DESCRIPTION
				"Pre roll read by the module"
		::= { hop3147c02v1Entry 385 }

		-- 1.3.6.1.4.1.10106.3.101291.1.1.387
		hop3147c02v1Scte104RxBrkd OBJECT-TYPE
			SYNTAX BreakDuration
			MAX-ACCESS read-only
			STATUS current
			DESCRIPTION
				"Break duration read by the module"
		::= { hop3147c02v1Entry 387 }

		-- 1.3.6.1.4.1.10106.3.101291.1.1.389
		hop3147c02v1Scte104ContRx OBJECT-TYPE
			SYNTAX Uint8
			MAX-ACCESS read-only
			STATUS current
			DESCRIPTION
				"Message number of the last correct packet received."
		::= { hop3147c02v1Entry 389 }

		-- 1.3.6.1.4.1.10106.3.101291.1.1.391
		hop3147c02v1LtcInsEn OBJECT-TYPE
			SYNTAX VitcLtc
			MAX-ACCESS read-write
			STATUS current
			DESCRIPTION
				"VITC - LTC selection"
		::= { hop3147c02v1Entry 391 }

		-- 1.3.6.1.4.1.10106.3.101291.1.1.393
		hop3147c02v1DtmfInsEn OBJECT-TYPE
			SYNTAX Bit0No1Yes
			MAX-ACCESS read-write
			STATUS current
			DESCRIPTION
				"Global insertion enable"
		::= { hop3147c02v1Entry 393 }

		-- 1.3.6.1.4.1.10106.3.101291.1.1.395
		hop3147c02v1DtmfGpi5En OBJECT-TYPE
			SYNTAX Bit0No1Yes
			MAX-ACCESS read-write
			STATUS current
			DESCRIPTION
				"GPI5 sends Cue Tone 1"
		::= { hop3147c02v1Entry 395 }

		-- 1.3.6.1.4.1.10106.3.101291.1.1.397
		hop3147c02v1DtmfGpi6En OBJECT-TYPE
			SYNTAX Bit0No1Yes
			MAX-ACCESS read-write
			STATUS current
			DESCRIPTION
				"GPI6 sends Cue Tone 2"
		::= { hop3147c02v1Entry 397 }

		-- 1.3.6.1.4.1.10106.3.101291.1.1.399
		hop3147c02v1DtmfGpi7En OBJECT-TYPE
			SYNTAX Bit0No1Yes
			MAX-ACCESS read-write
			STATUS current
			DESCRIPTION
				"GPI7 sends Cue Tone 3"
		::= { hop3147c02v1Entry 399 }

		-- 1.3.6.1.4.1.10106.3.101291.1.1.401
		hop3147c02v1DtmfGpi8En OBJECT-TYPE
			SYNTAX Bit0No1Yes
			MAX-ACCESS read-write
			STATUS current
			DESCRIPTION
				"GPI8 sends Cue Tone 4"
		::= { hop3147c02v1Entry 401 }

		-- 1.3.6.1.4.1.10106.3.101291.1.1.403
		hop3147c02v1DtmfChannel OBJECT-TYPE
			SYNTAX AudioMxInput6
			MAX-ACCESS read-write
			STATUS current
			DESCRIPTION
				"Insertion channel"
		::= { hop3147c02v1Entry 403 }

		-- 1.3.6.1.4.1.10106.3.101291.1.1.405
		hop3147c02v1DtmfPairEn OBJECT-TYPE
			SYNTAX Bit0No1Yes
			MAX-ACCESS read-write
			STATUS current
			DESCRIPTION
				"Uses the two channels of pair"
		::= { hop3147c02v1Entry 405 }

		-- 1.3.6.1.4.1.10106.3.101291.1.1.407
		hop3147c02v1DtmfLevel OBJECT-TYPE
			SYNTAX LevelDbfsF
			MAX-ACCESS read-write
			STATUS current
			DESCRIPTION
				"Audio level in dBFS"
		::= { hop3147c02v1Entry 407 }

		-- 1.3.6.1.4.1.10106.3.101291.1.1.409
		hop3147c02v1DtmfCode11 OBJECT-TYPE
			SYNTAX DtmfCode
			MAX-ACCESS read-write
			STATUS current
			DESCRIPTION
				"Cue Tone 1 code 1"
		::= { hop3147c02v1Entry 409 }

		-- 1.3.6.1.4.1.10106.3.101291.1.1.411
		hop3147c02v1DtmfCode12 OBJECT-TYPE
			SYNTAX DtmfCode
			MAX-ACCESS read-write
			STATUS current
			DESCRIPTION
				"Cue Tone 1 code 2"
		::= { hop3147c02v1Entry 411 }

		-- 1.3.6.1.4.1.10106.3.101291.1.1.413
		hop3147c02v1DtmfCode13 OBJECT-TYPE
			SYNTAX DtmfCode
			MAX-ACCESS read-write
			STATUS current
			DESCRIPTION
				"Cue Tone 1 code 3"
		::= { hop3147c02v1Entry 413 }

		-- 1.3.6.1.4.1.10106.3.101291.1.1.415
		hop3147c02v1DtmfCode14 OBJECT-TYPE
			SYNTAX DtmfCode
			MAX-ACCESS read-write
			STATUS current
			DESCRIPTION
				"Cue Tone 1 code 4"
		::= { hop3147c02v1Entry 415 }

		-- 1.3.6.1.4.1.10106.3.101291.1.1.417
		hop3147c02v1DtmfCode21 OBJECT-TYPE
			SYNTAX DtmfCode
			MAX-ACCESS read-write
			STATUS current
			DESCRIPTION
				"Cue Tone 2 code 1"
		::= { hop3147c02v1Entry 417 }

		-- 1.3.6.1.4.1.10106.3.101291.1.1.419
		hop3147c02v1DtmfCode22 OBJECT-TYPE
			SYNTAX DtmfCode
			MAX-ACCESS read-write
			STATUS current
			DESCRIPTION
				"Cue Tone 2 code 2"
		::= { hop3147c02v1Entry 419 }

		-- 1.3.6.1.4.1.10106.3.101291.1.1.421
		hop3147c02v1DtmfCode23 OBJECT-TYPE
			SYNTAX DtmfCode
			MAX-ACCESS read-write
			STATUS current
			DESCRIPTION
				"Cue Tone 2 code 3"
		::= { hop3147c02v1Entry 421 }

		-- 1.3.6.1.4.1.10106.3.101291.1.1.423
		hop3147c02v1DtmfCode24 OBJECT-TYPE
			SYNTAX DtmfCode
			MAX-ACCESS read-write
			STATUS current
			DESCRIPTION
				"Cue Tone 2 code 4"
		::= { hop3147c02v1Entry 423 }

		-- 1.3.6.1.4.1.10106.3.101291.1.1.425
		hop3147c02v1DtmfCode31 OBJECT-TYPE
			SYNTAX DtmfCode
			MAX-ACCESS read-write
			STATUS current
			DESCRIPTION
				"Cue Tone 3 code 1"
		::= { hop3147c02v1Entry 425 }

		-- 1.3.6.1.4.1.10106.3.101291.1.1.427
		hop3147c02v1DtmfCode32 OBJECT-TYPE
			SYNTAX DtmfCode
			MAX-ACCESS read-write
			STATUS current
			DESCRIPTION
				"Cue Tone 3 code 2"
		::= { hop3147c02v1Entry 427 }

		-- 1.3.6.1.4.1.10106.3.101291.1.1.429
		hop3147c02v1DtmfCode33 OBJECT-TYPE
			SYNTAX DtmfCode
			MAX-ACCESS read-write
			STATUS current
			DESCRIPTION
				"Cue Tone 3 code 3"
		::= { hop3147c02v1Entry 429 }

		-- 1.3.6.1.4.1.10106.3.101291.1.1.431
		hop3147c02v1DtmfCode34 OBJECT-TYPE
			SYNTAX DtmfCode
			MAX-ACCESS read-write
			STATUS current
			DESCRIPTION
				"Cue Tone 3 code 4"
		::= { hop3147c02v1Entry 431 }

		-- 1.3.6.1.4.1.10106.3.101291.1.1.433
		hop3147c02v1DtmfCode41 OBJECT-TYPE
			SYNTAX DtmfCode
			MAX-ACCESS read-write
			STATUS current
			DESCRIPTION
				"Cue Tone 4 code 1"
		::= { hop3147c02v1Entry 433 }

		-- 1.3.6.1.4.1.10106.3.101291.1.1.435
		hop3147c02v1DtmfCode42 OBJECT-TYPE
			SYNTAX DtmfCode
			MAX-ACCESS read-write
			STATUS current
			DESCRIPTION
				"Cue Tone 4 code 2"
		::= { hop3147c02v1Entry 435 }

		-- 1.3.6.1.4.1.10106.3.101291.1.1.437
		hop3147c02v1DtmfCode43 OBJECT-TYPE
			SYNTAX DtmfCode
			MAX-ACCESS read-write
			STATUS current
			DESCRIPTION
				"Cue Tone 4 code 3"
		::= { hop3147c02v1Entry 437 }

		-- 1.3.6.1.4.1.10106.3.101291.1.1.439
		hop3147c02v1DtmfCode44 OBJECT-TYPE
			SYNTAX DtmfCode
			MAX-ACCESS read-write
			STATUS current
			DESCRIPTION
				"Cue Tone 4 code 4"
		::= { hop3147c02v1Entry 439 }

		-- 1.3.6.1.4.1.10106.3.101291.1.1.441
		hop3147c02v1InsCode1 OBJECT-TYPE
			SYNTAX Bit0No1Yes
			MAX-ACCESS read-write
			STATUS current
			DESCRIPTION
				"Cue Tone 1 insertion"
		::= { hop3147c02v1Entry 441 }

		-- 1.3.6.1.4.1.10106.3.101291.1.1.443
		hop3147c02v1InsCode2 OBJECT-TYPE
			SYNTAX Bit0No1Yes
			MAX-ACCESS read-write
			STATUS current
			DESCRIPTION
				"Cue Tone 2 insertion"
		::= { hop3147c02v1Entry 443 }

		-- 1.3.6.1.4.1.10106.3.101291.1.1.445
		hop3147c02v1InsCode3 OBJECT-TYPE
			SYNTAX Bit0No1Yes
			MAX-ACCESS read-write
			STATUS current
			DESCRIPTION
				"Cue Tone 3 insertion"
		::= { hop3147c02v1Entry 445 }

		-- 1.3.6.1.4.1.10106.3.101291.1.1.447
		hop3147c02v1InsCode4 OBJECT-TYPE
			SYNTAX Bit0No1Yes
			MAX-ACCESS read-write
			STATUS current
			DESCRIPTION
				"Cue Tone 4 insertion"
		::= { hop3147c02v1Entry 447 }

		-- 1.3.6.1.4.1.10106.3.101291.1.1.449
		hop3147c02v1Scte104Ins OBJECT-TYPE
			SYNTAX Scte104Interva
			MAX-ACCESS read-write
			STATUS current
			DESCRIPTION
				"Number frames between insertions"
		::= { hop3147c02v1Entry 449 }

		-- 1.3.6.1.4.1.10106.3.101291.1.1.451
		hop3147c02v1SplStInmInEn OBJECT-TYPE
			SYNTAX Bit0No1Yes
			MAX-ACCESS read-write
			STATUS current
			DESCRIPTION
				"Enables insertion of splice start inmediate SCTE104 packets at intervals"
		::= { hop3147c02v1Entry 451 }

		-- 1.3.6.1.4.1.10106.3.101291.1.1.453
		hop3147c02v1SplStEndInEn OBJECT-TYPE
			SYNTAX Bit0No1Yes
			MAX-ACCESS read-write
			STATUS current
			DESCRIPTION
				"Enables insertion of splice end inmediate SCTE104 packets at intervals"
		::= { hop3147c02v1Entry 453 }

		-- 1.3.6.1.4.1.10106.3.101291.1.1.455
		hop3147c02v1Gpi7SplStaOn OBJECT-TYPE
			SYNTAX Bit0No1Yes
			MAX-ACCESS read-write
			STATUS current
			DESCRIPTION
				"Enables sending splice end inmediate SCTE 104 packet at intervals using GPI7"
		::= { hop3147c02v1Entry 455 }

		-- 1.3.6.1.4.1.10106.3.101291.1.1.457
		hop3147c02v1Gpi8SplStaOff OBJECT-TYPE
			SYNTAX Bit0No1Yes
			MAX-ACCESS read-write
			STATUS current
			DESCRIPTION
				"Stops sending splice end inmediate SCTE 104 packet at intervals using GPI8"
		::= { hop3147c02v1Entry 457 }

		-- 1.3.6.1.4.1.10106.3.413901
		kbd3160c01v1 OBJECT IDENTIFIER ::= { albalaProducts 413901 }

		-- 1.3.6.1.4.1.10106.3.413901.1
		kbd3160c01v1Table  OBJECT-TYPE
			SYNTAX SEQUENCE OF Kbd3160c01v1Entry
			MAX-ACCESS not-accessible
			STATUS current
			DESCRIPTION
				"Module  KBD3160C01V1 Table"
			::= { kbd3160c01v1 1 }

		-- 1.3.6.1.4.1.10106.3.413901.1.1
		kbd3160c01v1Entry  OBJECT-TYPE
			SYNTAX Kbd3160c01v1Entry
			MAX-ACCESS not-accessible
			STATUS current
			DESCRIPTION
				"Module KBD3160C01V1 Entry"
			INDEX { kbd3160c01v1Index }
			::= { kbd3160c01v1Table 1 }

			Kbd3160c01v1Entry ::=
			SEQUENCE {
				kbd3160c01v1Index
				ModuleIndex,
				kbd3160c01v1BeepEna
				Bit0No1Yes,
				kbd3160c01v1Brightness
				Brightness,
				kbd3160c01v1Gpo1
				Bit0Ina1Act,
				kbd3160c01v1Gpo2
				Bit0Ina1Act,
				kbd3160c01v1Gpo3
				Bit0Ina1Act,
				kbd3160c01v1Gpo4
				Bit0Ina1Act,
				kbd3160c01v1Gpo5
				Bit0Ina1Act,
				kbd3160c01v1Gpo6
				Bit0Ina1Act,
				kbd3160c01v1Gpo7
				Bit0Ina1Act,
				kbd3160c01v1Gpo8
				Bit0Ina1Act,
				kbd3160c01v1Gpo9
				Bit0Ina1Act,
				kbd3160c01v1Gpo10
				Bit0Ina1Act,
				kbd3160c01v1Gpo11
				Bit0Ina1Act,
				kbd3160c01v1Gpo12
				Bit0Ina1Act,
				kbd3160c01v1Gpo13
				Bit0Ina1Act,
				kbd3160c01v1Gpo14
				Bit0Ina1Act,
				kbd3160c01v1Gpo15
				Bit0Ina1Act,
				kbd3160c01v1Gpo16
				Bit0Ina1Act,
				kbd3160c01v1Gpi1
				Bit0Ina1Act,
				kbd3160c01v1Gpi2
				Bit0Ina1Act,
				kbd3160c01v1Gpi3
				Bit0Ina1Act,
				kbd3160c01v1Gpi4
				Bit0Ina1Act,
				kbd3160c01v1Gpi5
				Bit0Ina1Act,
				kbd3160c01v1Gpi6
				Bit0Ina1Act,
				kbd3160c01v1Gpi7
				Bit0Ina1Act,
				kbd3160c01v1Gpi8
				Bit0Ina1Act,
				kbd3160c01v1Gpi9
				Bit0Ina1Act,
				kbd3160c01v1Gpi10
				Bit0Ina1Act,
				kbd3160c01v1Gpi11
				Bit0Ina1Act,
				kbd3160c01v1Gpi12
				Bit0Ina1Act,
				kbd3160c01v1Gpi13
				Bit0Ina1Act,
				kbd3160c01v1Gpi14
				Bit0Ina1Act,
				kbd3160c01v1Gpi15
				Bit0Ina1Act,
				kbd3160c01v1Gpi16
				Bit0Ina1Act,
				kbd3160c01v1Psu0Fail
				BitFail,
				kbd3160c01v1Psu1Fail
				BitFail,
				kbd3160c01v1SerialNo
				SerialNo
			 }

		-- 1.3.6.1.4.1.10106.3.101291.1.1.1
		kbd3160c01v1Index OBJECT-TYPE
			SYNTAX ModuleIndex
			MAX-ACCESS read-only
			STATUS current
			DESCRIPTION
				"Index of KBD3160C01V1 Table"
		::= { kbd3160c01v1Entry 1 }

		-- 1.3.6.1.4.1.10106.3.101291.1.1.3
		kbd3160c01v1BeepEna OBJECT-TYPE
			SYNTAX Bit0No1Yes
			MAX-ACCESS read-write
			STATUS current
			DESCRIPTION
				"Allows that the keys make a beep when pressed or not"
		::= { kbd3160c01v1Entry 3 }

		-- 1.3.6.1.4.1.10106.3.101291.1.1.5
		kbd3160c01v1Brightness OBJECT-TYPE
			SYNTAX Brightness
			MAX-ACCESS read-write
			STATUS current
			DESCRIPTION
				"Allows changing key brightness"
		::= { kbd3160c01v1Entry 5 }

		-- 1.3.6.1.4.1.10106.3.101291.1.1.7
		kbd3160c01v1Gpo1 OBJECT-TYPE
			SYNTAX Bit0Ina1Act
			MAX-ACCESS read-write
			STATUS current
			DESCRIPTION
				"Allows control of GPO1"
		::= { kbd3160c01v1Entry 7 }

		-- 1.3.6.1.4.1.10106.3.101291.1.1.9
		kbd3160c01v1Gpo2 OBJECT-TYPE
			SYNTAX Bit0Ina1Act
			MAX-ACCESS read-write
			STATUS current
			DESCRIPTION
				"Allows control of GPO2"
		::= { kbd3160c01v1Entry 9 }

		-- 1.3.6.1.4.1.10106.3.101291.1.1.11
		kbd3160c01v1Gpo3 OBJECT-TYPE
			SYNTAX Bit0Ina1Act
			MAX-ACCESS read-write
			STATUS current
			DESCRIPTION
				"Allows control of GPO3"
		::= { kbd3160c01v1Entry 11 }

		-- 1.3.6.1.4.1.10106.3.101291.1.1.13
		kbd3160c01v1Gpo4 OBJECT-TYPE
			SYNTAX Bit0Ina1Act
			MAX-ACCESS read-write
			STATUS current
			DESCRIPTION
				"Allows control of GPO4"
		::= { kbd3160c01v1Entry 13 }

		-- 1.3.6.1.4.1.10106.3.101291.1.1.15
		kbd3160c01v1Gpo5 OBJECT-TYPE
			SYNTAX Bit0Ina1Act
			MAX-ACCESS read-write
			STATUS current
			DESCRIPTION
				"Allows control of GPO5"
		::= { kbd3160c01v1Entry 15 }

		-- 1.3.6.1.4.1.10106.3.101291.1.1.17
		kbd3160c01v1Gpo6 OBJECT-TYPE
			SYNTAX Bit0Ina1Act
			MAX-ACCESS read-write
			STATUS current
			DESCRIPTION
				"Allows control of GPO6"
		::= { kbd3160c01v1Entry 17 }

		-- 1.3.6.1.4.1.10106.3.101291.1.1.19
		kbd3160c01v1Gpo7 OBJECT-TYPE
			SYNTAX Bit0Ina1Act
			MAX-ACCESS read-write
			STATUS current
			DESCRIPTION
				"Allows control of GPO7"
		::= { kbd3160c01v1Entry 19 }

		-- 1.3.6.1.4.1.10106.3.101291.1.1.21
		kbd3160c01v1Gpo8 OBJECT-TYPE
			SYNTAX Bit0Ina1Act
			MAX-ACCESS read-write
			STATUS current
			DESCRIPTION
				"Allows control of GPO8"
		::= { kbd3160c01v1Entry 21 }

		-- 1.3.6.1.4.1.10106.3.101291.1.1.23
		kbd3160c01v1Gpo9 OBJECT-TYPE
			SYNTAX Bit0Ina1Act
			MAX-ACCESS read-write
			STATUS current
			DESCRIPTION
				"Allows control of GPO9"
		::= { kbd3160c01v1Entry 23 }

		-- 1.3.6.1.4.1.10106.3.101291.1.1.25
		kbd3160c01v1Gpo10 OBJECT-TYPE
			SYNTAX Bit0Ina1Act
			MAX-ACCESS read-write
			STATUS current
			DESCRIPTION
				"Allows control of GPO10"
		::= { kbd3160c01v1Entry 25 }

		-- 1.3.6.1.4.1.10106.3.101291.1.1.27
		kbd3160c01v1Gpo11 OBJECT-TYPE
			SYNTAX Bit0Ina1Act
			MAX-ACCESS read-write
			STATUS current
			DESCRIPTION
				"Allows control of GPO11"
		::= { kbd3160c01v1Entry 27 }

		-- 1.3.6.1.4.1.10106.3.101291.1.1.29
		kbd3160c01v1Gpo12 OBJECT-TYPE
			SYNTAX Bit0Ina1Act
			MAX-ACCESS read-write
			STATUS current
			DESCRIPTION
				"Allows control of GPO12"
		::= { kbd3160c01v1Entry 29 }

		-- 1.3.6.1.4.1.10106.3.101291.1.1.31
		kbd3160c01v1Gpo13 OBJECT-TYPE
			SYNTAX Bit0Ina1Act
			MAX-ACCESS read-write
			STATUS current
			DESCRIPTION
				"Allows control of GPO13"
		::= { kbd3160c01v1Entry 31 }

		-- 1.3.6.1.4.1.10106.3.101291.1.1.33
		kbd3160c01v1Gpo14 OBJECT-TYPE
			SYNTAX Bit0Ina1Act
			MAX-ACCESS read-write
			STATUS current
			DESCRIPTION
				"Allows control of GPO14"
		::= { kbd3160c01v1Entry 33 }

		-- 1.3.6.1.4.1.10106.3.101291.1.1.35
		kbd3160c01v1Gpo15 OBJECT-TYPE
			SYNTAX Bit0Ina1Act
			MAX-ACCESS read-write
			STATUS current
			DESCRIPTION
				"Allows control of GPO15"
		::= { kbd3160c01v1Entry 35 }

		-- 1.3.6.1.4.1.10106.3.101291.1.1.37
		kbd3160c01v1Gpo16 OBJECT-TYPE
			SYNTAX Bit0Ina1Act
			MAX-ACCESS read-write
			STATUS current
			DESCRIPTION
				"Allows control of GPO16"
		::= { kbd3160c01v1Entry 37 }

		-- 1.3.6.1.4.1.10106.3.101291.1.1.39
		kbd3160c01v1Gpi1 OBJECT-TYPE
			SYNTAX Bit0Ina1Act
			MAX-ACCESS read-only
			STATUS current
			DESCRIPTION
				"GPI1 status"
		::= { kbd3160c01v1Entry 39 }

		-- 1.3.6.1.4.1.10106.3.101291.1.1.41
		kbd3160c01v1Gpi2 OBJECT-TYPE
			SYNTAX Bit0Ina1Act
			MAX-ACCESS read-only
			STATUS current
			DESCRIPTION
				"GPI2 status"
		::= { kbd3160c01v1Entry 41 }

		-- 1.3.6.1.4.1.10106.3.101291.1.1.43
		kbd3160c01v1Gpi3 OBJECT-TYPE
			SYNTAX Bit0Ina1Act
			MAX-ACCESS read-only
			STATUS current
			DESCRIPTION
				"GPI3 status"
		::= { kbd3160c01v1Entry 43 }

		-- 1.3.6.1.4.1.10106.3.101291.1.1.45
		kbd3160c01v1Gpi4 OBJECT-TYPE
			SYNTAX Bit0Ina1Act
			MAX-ACCESS read-only
			STATUS current
			DESCRIPTION
				"GPI4 status"
		::= { kbd3160c01v1Entry 45 }

		-- 1.3.6.1.4.1.10106.3.101291.1.1.47
		kbd3160c01v1Gpi5 OBJECT-TYPE
			SYNTAX Bit0Ina1Act
			MAX-ACCESS read-only
			STATUS current
			DESCRIPTION
				"GPI5 status"
		::= { kbd3160c01v1Entry 47 }

		-- 1.3.6.1.4.1.10106.3.101291.1.1.49
		kbd3160c01v1Gpi6 OBJECT-TYPE
			SYNTAX Bit0Ina1Act
			MAX-ACCESS read-only
			STATUS current
			DESCRIPTION
				"GPI6 status"
		::= { kbd3160c01v1Entry 49 }

		-- 1.3.6.1.4.1.10106.3.101291.1.1.51
		kbd3160c01v1Gpi7 OBJECT-TYPE
			SYNTAX Bit0Ina1Act
			MAX-ACCESS read-only
			STATUS current
			DESCRIPTION
				"GPI7 status"
		::= { kbd3160c01v1Entry 51 }

		-- 1.3.6.1.4.1.10106.3.101291.1.1.53
		kbd3160c01v1Gpi8 OBJECT-TYPE
			SYNTAX Bit0Ina1Act
			MAX-ACCESS read-only
			STATUS current
			DESCRIPTION
				"GPI8 status"
		::= { kbd3160c01v1Entry 53 }

		-- 1.3.6.1.4.1.10106.3.101291.1.1.55
		kbd3160c01v1Gpi9 OBJECT-TYPE
			SYNTAX Bit0Ina1Act
			MAX-ACCESS read-only
			STATUS current
			DESCRIPTION
				"GPI9 status"
		::= { kbd3160c01v1Entry 55 }

		-- 1.3.6.1.4.1.10106.3.101291.1.1.57
		kbd3160c01v1Gpi10 OBJECT-TYPE
			SYNTAX Bit0Ina1Act
			MAX-ACCESS read-only
			STATUS current
			DESCRIPTION
				"GPI10 status"
		::= { kbd3160c01v1Entry 57 }

		-- 1.3.6.1.4.1.10106.3.101291.1.1.59
		kbd3160c01v1Gpi11 OBJECT-TYPE
			SYNTAX Bit0Ina1Act
			MAX-ACCESS read-only
			STATUS current
			DESCRIPTION
				"GPI11 status"
		::= { kbd3160c01v1Entry 59 }

		-- 1.3.6.1.4.1.10106.3.101291.1.1.61
		kbd3160c01v1Gpi12 OBJECT-TYPE
			SYNTAX Bit0Ina1Act
			MAX-ACCESS read-only
			STATUS current
			DESCRIPTION
				"GPI12 status"
		::= { kbd3160c01v1Entry 61 }

		-- 1.3.6.1.4.1.10106.3.101291.1.1.63
		kbd3160c01v1Gpi13 OBJECT-TYPE
			SYNTAX Bit0Ina1Act
			MAX-ACCESS read-only
			STATUS current
			DESCRIPTION
				"GPI13 status"
		::= { kbd3160c01v1Entry 63 }

		-- 1.3.6.1.4.1.10106.3.101291.1.1.65
		kbd3160c01v1Gpi14 OBJECT-TYPE
			SYNTAX Bit0Ina1Act
			MAX-ACCESS read-only
			STATUS current
			DESCRIPTION
				"GPI14 status"
		::= { kbd3160c01v1Entry 65 }

		-- 1.3.6.1.4.1.10106.3.101291.1.1.67
		kbd3160c01v1Gpi15 OBJECT-TYPE
			SYNTAX Bit0Ina1Act
			MAX-ACCESS read-only
			STATUS current
			DESCRIPTION
				"GPI15 status"
		::= { kbd3160c01v1Entry 67 }

		-- 1.3.6.1.4.1.10106.3.101291.1.1.69
		kbd3160c01v1Gpi16 OBJECT-TYPE
			SYNTAX Bit0Ina1Act
			MAX-ACCESS read-only
			STATUS current
			DESCRIPTION
				"GPI16 status"
		::= { kbd3160c01v1Entry 69 }

		-- 1.3.6.1.4.1.10106.3.101291.1.1.71
		kbd3160c01v1Psu0Fail OBJECT-TYPE
			SYNTAX BitFail
			MAX-ACCESS read-only
			STATUS current
			DESCRIPTION
				"Indicates fail in power supply 1"
		::= { kbd3160c01v1Entry 71 }

		-- 1.3.6.1.4.1.10106.3.101291.1.1.73
		kbd3160c01v1Psu1Fail OBJECT-TYPE
			SYNTAX BitFail
			MAX-ACCESS read-only
			STATUS current
			DESCRIPTION
				"Indicates fail in power supply 2"
		::= { kbd3160c01v1Entry 73 }

		-- 1.3.6.1.4.1.10106.3.101291.1.1.75
		kbd3160c01v1SerialNo OBJECT-TYPE
			SYNTAX SerialNo
			MAX-ACCESS read-only
			STATUS current
			DESCRIPTION
				"Serial number"
		::= { kbd3160c01v1Entry 75 }

		-- 1.3.6.1.4.1.10106.3.415501
		act3000c01v1 OBJECT IDENTIFIER ::= { albalaProducts 415501 }

		-- 1.3.6.1.4.1.10106.3.415501.1
		act3000c01v1Table  OBJECT-TYPE
			SYNTAX SEQUENCE OF Act3000c01v1Entry
			MAX-ACCESS not-accessible
			STATUS current
			DESCRIPTION
				"Module  ACT3000C01V1 Table"
			::= { act3000c01v1 1 }

		-- 1.3.6.1.4.1.10106.3.415501.1.1
		act3000c01v1Entry  OBJECT-TYPE
			SYNTAX Act3000c01v1Entry
			MAX-ACCESS not-accessible
			STATUS current
			DESCRIPTION
				"Module ACT3000C01V1 Entry"
			INDEX { act3000c01v1Index }
			::= { act3000c01v1Table 1 }

			Act3000c01v1Entry ::=
			SEQUENCE {
				act3000c01v1Index
				ModuleIndex,
				act3000c01v1ActivePreset
				Preset16Active,
				act3000c01v1LoadPreset
				Preset16Load,
				act3000c01v1SavePreset
				Preset16Save,
				act3000c01v1StateSel
				HswState,
				act3000c01v1StateSelTrapEnable
				AlarmEnable,
				act3000c01v1In1StChange
				Bit0No1Yes,
				act3000c01v1In2StChange
				Bit0No1Yes,
				act3000c01v1Gpi1StChange
				Bit0No1Yes,
				act3000c01v1Gpi2StChange
				Bit0No1Yes,
				act3000c01v1InputChange
				Bit0No1Yes,
				act3000c01v1StatusChange
				Bit0No1Yes,
				act3000c01v1SwitchMode
				ActSwMode,
				act3000c01v1SwitchModeTrapEnable
				AlarmEnable,
				act3000c01v1StateAMapOut
				HswMapState,
				act3000c01v1StateAMapGpo
				ActGpoState,
				act3000c01v1StateBMapOut
				HswMapState,
				act3000c01v1StateBMapGpo
				ActGpoState,
				act3000c01v1Holdoff
				TimeS2,
				act3000c01v1ActPer1
				TimeS2,
				act3000c01v1DeactPer1
				TimeS2,
				act3000c01v1ActPer2
				TimeS2,
				act3000c01v1DeactPer2
				TimeS2,
				act3000c01v1SilenceLevel
				LevelDbfs3,
				act3000c01v1OvldLevel
				LevelDbfs4,
				act3000c01v1ClippingLevel
				LevelDbu,
				act3000c01v1AntiphLevel
				PhaseCor,
				act3000c01v1SilFailTim
				HswTiming,
				act3000c01v1OvldFailTim
				HswTiming,
				act3000c01v1AntiphFailTim
				HswTiming,
				act3000c01v1GpiFailTim
				HswTiming,
				act3000c01v1MeasSil1
				Bit0LdBit1Pk2,
				act3000c01v1MeasSil2
				Bit0LdBit1Pk2,
				act3000c01v1MeasOvld1
				Bit0LdBit1Pk2,
				act3000c01v1MeasOvld2
				Bit0LdBit1Pk2,
				act3000c01v1LoudSel
				Bit0MBit1S,
				act3000c01v1PairIn1
				Bit0Ste1Mon,
				act3000c01v1PairIn2
				Bit0Ste1Mon,
				act3000c01v1GpoCfg
				Bit0Alrm1Sta,
				act3000c01v1SmoothDel
				DelayAud,
				act3000c01v1SmoothDelTime
				TimeX10Ms2,
				act3000c01v1Delay1l
				DelayAud,
				act3000c01v1Gain1l
				Gain24dbMute,
				act3000c01v1Phase1l
				Bit0Nor1Inv,
				act3000c01v1Delay1r
				DelayAud,
				act3000c01v1Gain1r
				Gain24dbMute,
				act3000c01v1Phase1r
				Bit0Nor1Inv,
				act3000c01v1Delay2l
				DelayAud,
				act3000c01v1Gain2l
				Gain24dbMute,
				act3000c01v1Phase2l
				Bit0Nor1Inv,
				act3000c01v1Delay2r
				DelayAud,
				act3000c01v1Gain2r
				Gain24dbMute,
				act3000c01v1Phase2r
				Bit0Nor1Inv,
				act3000c01v1StatFlash
				BitFailN,
				act3000c01v1StatusIn1
				BitFail,
				act3000c01v1StatusIn1TrapEnable
				AlarmEnable,
				act3000c01v1StatusIn2
				BitFail,
				act3000c01v1StatusIn2TrapEnable
				AlarmEnable,
				act3000c01v1StatusIn1Ext
				BitFail,
				act3000c01v1StatusIn1ExtTrapEnable
				AlarmEnable,
				act3000c01v1StatusIn2Ext
				BitFail,
				act3000c01v1StatusIn2ExtTrapEnable
				AlarmEnable,
				act3000c01v1StatusIn1Clip
				BitFail,
				act3000c01v1StatusIn1ClipTrapEnable
				AlarmEnable,
				act3000c01v1StatusIn2Clip
				BitFail,
				act3000c01v1StatusIn2ClipTrapEnable
				AlarmEnable,
				act3000c01v1SelOut1
				ActMapState,
				act3000c01v1SelOut1TrapEnable
				AlarmEnable,
				act3000c01v1SelOut2
				ActMapState,
				act3000c01v1SelOut2TrapEnable
				AlarmEnable,
				act3000c01v1Gpo1Out
				Bit0Ina1Act,
				act3000c01v1Gpo2Out
				Bit0Ina1Act,
				act3000c01v1Gpi1Stat
				BitFail,
				act3000c01v1Gpi1StatTrapEnable
				AlarmEnable,
				act3000c01v1FailSil1l
				BitFail,
				act3000c01v1FailSil1lTrapEnable
				AlarmEnable,
				act3000c01v1FailOvld1l
				BitFail,
				act3000c01v1FailOvld1lTrapEnable
				AlarmEnable,
				act3000c01v1FailClip1l
				BitFail,
				act3000c01v1FailClip1lTrapEnable
				AlarmEnable,
				act3000c01v1FailAnti1
				BitFail,
				act3000c01v1FailAnti1TrapEnable
				AlarmEnable,
				act3000c01v1FailSil1r
				BitFail,
				act3000c01v1FailSil1rTrapEnable
				AlarmEnable,
				act3000c01v1FailOvld1r
				BitFail,
				act3000c01v1FailOvld1rTrapEnable
				AlarmEnable,
				act3000c01v1FailClip1r
				BitFail,
				act3000c01v1FailClip1rTrapEnable
				AlarmEnable,
				act3000c01v1FailExt1
				BitFail,
				act3000c01v1FailExt1TrapEnable
				AlarmEnable,
				act3000c01v1FailSil2l
				BitFail,
				act3000c01v1FailSil2lTrapEnable
				AlarmEnable,
				act3000c01v1FailOvld2l
				BitFail,
				act3000c01v1FailOvld2lTrapEnable
				AlarmEnable,
				act3000c01v1FailClip2l
				BitFail,
				act3000c01v1FailClip2lTrapEnable
				AlarmEnable,
				act3000c01v1FailAnti2
				BitFail,
				act3000c01v1FailAnti2TrapEnable
				AlarmEnable,
				act3000c01v1FailSil2r
				BitFail,
				act3000c01v1FailSil2rTrapEnable
				AlarmEnable,
				act3000c01v1FailOvld2r
				BitFail,
				act3000c01v1FailOvld2rTrapEnable
				AlarmEnable,
				act3000c01v1FailClip2r
				BitFail,
				act3000c01v1FailClip2rTrapEnable
				AlarmEnable,
				act3000c01v1FailExt2
				BitFail,
				act3000c01v1FailExt2TrapEnable
				AlarmEnable,
				act3000c01v1CurrentSmooth
				BitFail,
				act3000c01v1SerialNo
				SerialNo
			 }

		-- 1.3.6.1.4.1.10106.3.101291.1.1.1
		act3000c01v1Index OBJECT-TYPE
			SYNTAX ModuleIndex
			MAX-ACCESS read-only
			STATUS current
			DESCRIPTION
				"Index of ACT3000C01V1 Table"
		::= { act3000c01v1Entry 1 }

		-- 1.3.6.1.4.1.10106.3.101291.1.1.3
		act3000c01v1ActivePreset OBJECT-TYPE
			SYNTAX Preset16Active
			MAX-ACCESS read-only
			STATUS current
			DESCRIPTION
				"Shows the active preset"
		::= { act3000c01v1Entry 3 }

		-- 1.3.6.1.4.1.10106.3.101291.1.1.5
		act3000c01v1LoadPreset OBJECT-TYPE
			SYNTAX Preset16Load
			MAX-ACCESS read-write
			STATUS current
			DESCRIPTION
				"Allows loading a preset"
		::= { act3000c01v1Entry 5 }

		-- 1.3.6.1.4.1.10106.3.101291.1.1.7
		act3000c01v1SavePreset OBJECT-TYPE
			SYNTAX Preset16Save
			MAX-ACCESS read-write
			STATUS current
			DESCRIPTION
				"Allows saving a preset"
		::= { act3000c01v1Entry 7 }

		-- 1.3.6.1.4.1.10106.3.101291.1.1.9
		act3000c01v1StateSel OBJECT-TYPE
			SYNTAX HswState
			MAX-ACCESS read-write
			STATUS current
			DESCRIPTION
				"Shows the module's current state"
		::= { act3000c01v1Entry 9 }

		-- 1.3.6.1.4.1.10106.3.101291.1.1.10
		act3000c01v1StateSelTrapEnable OBJECT-TYPE
			SYNTAX AlarmEnable
			MAX-ACCESS read-write
			STATUS current
			DESCRIPTION
				"Shows the module's current state Trap Enable"
		::= { act3000c01v1Entry 10 }

		-- 1.3.6.1.4.1.10106.3.101291.1.1.11
		act3000c01v1In1StChange OBJECT-TYPE
			SYNTAX Bit0No1Yes
			MAX-ACCESS read-write
			STATUS current
			DESCRIPTION
				"Signals a change in fail status"
		::= { act3000c01v1Entry 11 }

		-- 1.3.6.1.4.1.10106.3.101291.1.1.13
		act3000c01v1In2StChange OBJECT-TYPE
			SYNTAX Bit0No1Yes
			MAX-ACCESS read-write
			STATUS current
			DESCRIPTION
				"Signals a change in fail status"
		::= { act3000c01v1Entry 13 }

		-- 1.3.6.1.4.1.10106.3.101291.1.1.15
		act3000c01v1Gpi1StChange OBJECT-TYPE
			SYNTAX Bit0No1Yes
			MAX-ACCESS read-write
			STATUS current
			DESCRIPTION
				"Signals a change in GPI fail status"
		::= { act3000c01v1Entry 15 }

		-- 1.3.6.1.4.1.10106.3.101291.1.1.17
		act3000c01v1Gpi2StChange OBJECT-TYPE
			SYNTAX Bit0No1Yes
			MAX-ACCESS read-write
			STATUS current
			DESCRIPTION
				"Signals a change in GPI fail status"
		::= { act3000c01v1Entry 17 }

		-- 1.3.6.1.4.1.10106.3.101291.1.1.19
		act3000c01v1InputChange OBJECT-TYPE
			SYNTAX Bit0No1Yes
			MAX-ACCESS read-write
			STATUS current
			DESCRIPTION
				"Signals a change in selected input"
		::= { act3000c01v1Entry 19 }

		-- 1.3.6.1.4.1.10106.3.101291.1.1.21
		act3000c01v1StatusChange OBJECT-TYPE
			SYNTAX Bit0No1Yes
			MAX-ACCESS read-write
			STATUS current
			DESCRIPTION
				"Signals a change in fail status"
		::= { act3000c01v1Entry 21 }

		-- 1.3.6.1.4.1.10106.3.101291.1.1.23
		act3000c01v1SwitchMode OBJECT-TYPE
			SYNTAX ActSwMode
			MAX-ACCESS read-write
			STATUS current
			DESCRIPTION
				"Allows selecting the switching mode"
		::= { act3000c01v1Entry 23 }

		-- 1.3.6.1.4.1.10106.3.101291.1.1.24
		act3000c01v1SwitchModeTrapEnable OBJECT-TYPE
			SYNTAX AlarmEnable
			MAX-ACCESS read-write
			STATUS current
			DESCRIPTION
				"Allows selecting the switching mode Trap Enable"
		::= { act3000c01v1Entry 24 }

		-- 1.3.6.1.4.1.10106.3.101291.1.1.25
		act3000c01v1StateAMapOut OBJECT-TYPE
			SYNTAX HswMapState
			MAX-ACCESS read-write
			STATUS current
			DESCRIPTION
				"Allow selecting the input to output mapping when state A is selected"
		::= { act3000c01v1Entry 25 }

		-- 1.3.6.1.4.1.10106.3.101291.1.1.27
		act3000c01v1StateAMapGpo OBJECT-TYPE
			SYNTAX ActGpoState
			MAX-ACCESS read-write
			STATUS current
			DESCRIPTION
				"Allow selecting the GPOs mapping when state A is selected"
		::= { act3000c01v1Entry 27 }

		-- 1.3.6.1.4.1.10106.3.101291.1.1.29
		act3000c01v1StateBMapOut OBJECT-TYPE
			SYNTAX HswMapState
			MAX-ACCESS read-write
			STATUS current
			DESCRIPTION
				"Allow selecting the input to output mapping when state B is selected"
		::= { act3000c01v1Entry 29 }

		-- 1.3.6.1.4.1.10106.3.101291.1.1.31
		act3000c01v1StateBMapGpo OBJECT-TYPE
			SYNTAX ActGpoState
			MAX-ACCESS read-write
			STATUS current
			DESCRIPTION
				"Allow selecting the GPOs mapping when state B is selected"
		::= { act3000c01v1Entry 31 }

		-- 1.3.6.1.4.1.10106.3.101291.1.1.33
		act3000c01v1Holdoff OBJECT-TYPE
			SYNTAX TimeS2
			MAX-ACCESS read-write
			STATUS current
			DESCRIPTION
				"Elapsed time after a switch event before a new switch occurs"
		::= { act3000c01v1Entry 33 }

		-- 1.3.6.1.4.1.10106.3.101291.1.1.35
		act3000c01v1ActPer1 OBJECT-TYPE
			SYNTAX TimeS2
			MAX-ACCESS read-write
			STATUS current
			DESCRIPTION
				"Activation time used in timing 1"
		::= { act3000c01v1Entry 35 }

		-- 1.3.6.1.4.1.10106.3.101291.1.1.37
		act3000c01v1DeactPer1 OBJECT-TYPE
			SYNTAX TimeS2
			MAX-ACCESS read-write
			STATUS current
			DESCRIPTION
				"Deactivation time used in timing 1"
		::= { act3000c01v1Entry 37 }

		-- 1.3.6.1.4.1.10106.3.101291.1.1.39
		act3000c01v1ActPer2 OBJECT-TYPE
			SYNTAX TimeS2
			MAX-ACCESS read-write
			STATUS current
			DESCRIPTION
				"Activation time used in timing 2"
		::= { act3000c01v1Entry 39 }

		-- 1.3.6.1.4.1.10106.3.101291.1.1.41
		act3000c01v1DeactPer2 OBJECT-TYPE
			SYNTAX TimeS2
			MAX-ACCESS read-write
			STATUS current
			DESCRIPTION
				"Deactivation time used in timing 2"
		::= { act3000c01v1Entry 41 }

		-- 1.3.6.1.4.1.10106.3.101291.1.1.43
		act3000c01v1SilenceLevel OBJECT-TYPE
			SYNTAX LevelDbfs3
			MAX-ACCESS read-write
			STATUS current
			DESCRIPTION
				"Allows adjusting the threshold level for the silence detector"
		::= { act3000c01v1Entry 43 }

		-- 1.3.6.1.4.1.10106.3.101291.1.1.45
		act3000c01v1OvldLevel OBJECT-TYPE
			SYNTAX LevelDbfs4
			MAX-ACCESS read-write
			STATUS current
			DESCRIPTION
				"Allows adjusting the threshold level for the overload detector"
		::= { act3000c01v1Entry 45 }

		-- 1.3.6.1.4.1.10106.3.101291.1.1.47
		act3000c01v1ClippingLevel OBJECT-TYPE
			SYNTAX LevelDbu
			MAX-ACCESS read-write
			STATUS current
			DESCRIPTION
				"Full scale level"
		::= { act3000c01v1Entry 47 }

		-- 1.3.6.1.4.1.10106.3.101291.1.1.49
		act3000c01v1AntiphLevel OBJECT-TYPE
			SYNTAX PhaseCor
			MAX-ACCESS read-write
			STATUS current
			DESCRIPTION
				"Antiphase level threshold"
		::= { act3000c01v1Entry 49 }

		-- 1.3.6.1.4.1.10106.3.101291.1.1.51
		act3000c01v1SilFailTim OBJECT-TYPE
			SYNTAX HswTiming
			MAX-ACCESS read-write
			STATUS current
			DESCRIPTION
				"Allows selecting the desired timing for the silence level fail"
		::= { act3000c01v1Entry 51 }

		-- 1.3.6.1.4.1.10106.3.101291.1.1.53
		act3000c01v1OvldFailTim OBJECT-TYPE
			SYNTAX HswTiming
			MAX-ACCESS read-write
			STATUS current
			DESCRIPTION
				"Allows selecting the desired timing for the overload level fail"
		::= { act3000c01v1Entry 53 }

		-- 1.3.6.1.4.1.10106.3.101291.1.1.55
		act3000c01v1AntiphFailTim OBJECT-TYPE
			SYNTAX HswTiming
			MAX-ACCESS read-write
			STATUS current
			DESCRIPTION
				"Allows selecting the desired timing for the antiphase fail"
		::= { act3000c01v1Entry 55 }

		-- 1.3.6.1.4.1.10106.3.101291.1.1.57
		act3000c01v1GpiFailTim OBJECT-TYPE
			SYNTAX HswTiming
			MAX-ACCESS read-write
			STATUS current
			DESCRIPTION
				"Allows selecting the desired timing for the GPI fail"
		::= { act3000c01v1Entry 57 }

		-- 1.3.6.1.4.1.10106.3.101291.1.1.59
		act3000c01v1MeasSil1 OBJECT-TYPE
			SYNTAX Bit0LdBit1Pk2
			MAX-ACCESS read-write
			STATUS current
			DESCRIPTION
				"Allows selecting the desired measurement for silence assessment"
		::= { act3000c01v1Entry 59 }

		-- 1.3.6.1.4.1.10106.3.101291.1.1.61
		act3000c01v1MeasSil2 OBJECT-TYPE
			SYNTAX Bit0LdBit1Pk2
			MAX-ACCESS read-write
			STATUS current
			DESCRIPTION
				"Allows selecting the desired measurement for silence assessment"
		::= { act3000c01v1Entry 61 }

		-- 1.3.6.1.4.1.10106.3.101291.1.1.63
		act3000c01v1MeasOvld1 OBJECT-TYPE
			SYNTAX Bit0LdBit1Pk2
			MAX-ACCESS read-write
			STATUS current
			DESCRIPTION
				"Allows selecting the desired measurement for overload assessment"
		::= { act3000c01v1Entry 63 }

		-- 1.3.6.1.4.1.10106.3.101291.1.1.65
		act3000c01v1MeasOvld2 OBJECT-TYPE
			SYNTAX Bit0LdBit1Pk2
			MAX-ACCESS read-write
			STATUS current
			DESCRIPTION
				"Allows selecting the desired measurement for overload assessment"
		::= { act3000c01v1Entry 65 }

		-- 1.3.6.1.4.1.10106.3.101291.1.1.67
		act3000c01v1LoudSel OBJECT-TYPE
			SYNTAX Bit0MBit1S
			MAX-ACCESS read-write
			STATUS current
			DESCRIPTION
				"Allows selecting the desired loudness measurement"
		::= { act3000c01v1Entry 67 }

		-- 1.3.6.1.4.1.10106.3.101291.1.1.69
		act3000c01v1PairIn1 OBJECT-TYPE
			SYNTAX Bit0Ste1Mon
			MAX-ACCESS read-write
			STATUS current
			DESCRIPTION
				"Allows configuring the audio scheme of input 1 as a stereophonic pair of two monophonic channels"
		::= { act3000c01v1Entry 69 }

		-- 1.3.6.1.4.1.10106.3.101291.1.1.71
		act3000c01v1PairIn2 OBJECT-TYPE
			SYNTAX Bit0Ste1Mon
			MAX-ACCESS read-write
			STATUS current
			DESCRIPTION
				"Allows configuring the audio scheme of input 2 as a stereophonic pair of two monophonic channels"
		::= { act3000c01v1Entry 71 }

		-- 1.3.6.1.4.1.10106.3.101291.1.1.73
		act3000c01v1GpoCfg OBJECT-TYPE
			SYNTAX Bit0Alrm1Sta
			MAX-ACCESS read-write
			STATUS current
			DESCRIPTION
				"Allows configuring the GPOs meaning"
		::= { act3000c01v1Entry 73 }

		-- 1.3.6.1.4.1.10106.3.101291.1.1.75
		act3000c01v1SmoothDel OBJECT-TYPE
			SYNTAX DelayAud
			MAX-ACCESS read-write
			STATUS current
			DESCRIPTION
				"Delay to be changed smoothly"
		::= { act3000c01v1Entry 75 }

		-- 1.3.6.1.4.1.10106.3.101291.1.1.77
		act3000c01v1SmoothDelTime OBJECT-TYPE
			SYNTAX TimeX10Ms2
			MAX-ACCESS read-write
			STATUS current
			DESCRIPTION
				"Available time to perform the smooth delay change"
		::= { act3000c01v1Entry 77 }

		-- 1.3.6.1.4.1.10106.3.101291.1.1.79
		act3000c01v1Delay1l OBJECT-TYPE
			SYNTAX DelayAud
			MAX-ACCESS read-write
			STATUS current
			DESCRIPTION
				"Audio delay in the input audio channel 1L"
		::= { act3000c01v1Entry 79 }

		-- 1.3.6.1.4.1.10106.3.101291.1.1.81
		act3000c01v1Gain1l OBJECT-TYPE
			SYNTAX Gain24dbMute
			MAX-ACCESS read-write
			STATUS current
			DESCRIPTION
				"Gain applied to the input audio channel 1L"
		::= { act3000c01v1Entry 81 }

		-- 1.3.6.1.4.1.10106.3.101291.1.1.83
		act3000c01v1Phase1l OBJECT-TYPE
			SYNTAX Bit0Nor1Inv
			MAX-ACCESS read-write
			STATUS current
			DESCRIPTION
				"Phase gain applied to the inputl audio channel 1L"
		::= { act3000c01v1Entry 83 }

		-- 1.3.6.1.4.1.10106.3.101291.1.1.85
		act3000c01v1Delay1r OBJECT-TYPE
			SYNTAX DelayAud
			MAX-ACCESS read-write
			STATUS current
			DESCRIPTION
				"Audio delay in the input audio channel 1R"
		::= { act3000c01v1Entry 85 }

		-- 1.3.6.1.4.1.10106.3.101291.1.1.87
		act3000c01v1Gain1r OBJECT-TYPE
			SYNTAX Gain24dbMute
			MAX-ACCESS read-write
			STATUS current
			DESCRIPTION
				"Gain applied to the input audio channel 1R"
		::= { act3000c01v1Entry 87 }

		-- 1.3.6.1.4.1.10106.3.101291.1.1.89
		act3000c01v1Phase1r OBJECT-TYPE
			SYNTAX Bit0Nor1Inv
			MAX-ACCESS read-write
			STATUS current
			DESCRIPTION
				"Phase gain applied to the inputl audio channel 1R"
		::= { act3000c01v1Entry 89 }

		-- 1.3.6.1.4.1.10106.3.101291.1.1.91
		act3000c01v1Delay2l OBJECT-TYPE
			SYNTAX DelayAud
			MAX-ACCESS read-write
			STATUS current
			DESCRIPTION
				"Audio delay in the input audio channel 2L"
		::= { act3000c01v1Entry 91 }

		-- 1.3.6.1.4.1.10106.3.101291.1.1.93
		act3000c01v1Gain2l OBJECT-TYPE
			SYNTAX Gain24dbMute
			MAX-ACCESS read-write
			STATUS current
			DESCRIPTION
				"Gain applied to the input audio channel 2L"
		::= { act3000c01v1Entry 93 }

		-- 1.3.6.1.4.1.10106.3.101291.1.1.95
		act3000c01v1Phase2l OBJECT-TYPE
			SYNTAX Bit0Nor1Inv
			MAX-ACCESS read-write
			STATUS current
			DESCRIPTION
				"Phase gain applied to the inputl audio channel 2L"
		::= { act3000c01v1Entry 95 }

		-- 1.3.6.1.4.1.10106.3.101291.1.1.97
		act3000c01v1Delay2r OBJECT-TYPE
			SYNTAX DelayAud
			MAX-ACCESS read-write
			STATUS current
			DESCRIPTION
				"Audio delay in the input audio channel 2R"
		::= { act3000c01v1Entry 97 }

		-- 1.3.6.1.4.1.10106.3.101291.1.1.99
		act3000c01v1Gain2r OBJECT-TYPE
			SYNTAX Gain24dbMute
			MAX-ACCESS read-write
			STATUS current
			DESCRIPTION
				"Gain applied to the input audio channel 1LGain applied to the input audio channel 2R"
		::= { act3000c01v1Entry 99 }

		-- 1.3.6.1.4.1.10106.3.101291.1.1.101
		act3000c01v1Phase2r OBJECT-TYPE
			SYNTAX Bit0Nor1Inv
			MAX-ACCESS read-write
			STATUS current
			DESCRIPTION
				"Phase gain applied to the inputl audio channel 2R"
		::= { act3000c01v1Entry 101 }

		-- 1.3.6.1.4.1.10106.3.101291.1.1.103
		act3000c01v1StatFlash OBJECT-TYPE
			SYNTAX BitFailN
			MAX-ACCESS read-only
			STATUS current
			DESCRIPTION
				"Displays the Flash state"
		::= { act3000c01v1Entry 103 }

		-- 1.3.6.1.4.1.10106.3.101291.1.1.105
		act3000c01v1StatusIn1 OBJECT-TYPE
			SYNTAX BitFail
			MAX-ACCESS read-only
			STATUS current
			DESCRIPTION
				"Input 1 fail"
		::= { act3000c01v1Entry 105 }

		-- 1.3.6.1.4.1.10106.3.101291.1.1.106
		act3000c01v1StatusIn1TrapEnable OBJECT-TYPE
			SYNTAX AlarmEnable
			MAX-ACCESS read-write
			STATUS current
			DESCRIPTION
				"Input 1 fail Trap Enable"
		::= { act3000c01v1Entry 106 }

		-- 1.3.6.1.4.1.10106.3.101291.1.1.107
		act3000c01v1StatusIn2 OBJECT-TYPE
			SYNTAX BitFail
			MAX-ACCESS read-only
			STATUS current
			DESCRIPTION
				"Input 2 fail"
		::= { act3000c01v1Entry 107 }

		-- 1.3.6.1.4.1.10106.3.101291.1.1.108
		act3000c01v1StatusIn2TrapEnable OBJECT-TYPE
			SYNTAX AlarmEnable
			MAX-ACCESS read-write
			STATUS current
			DESCRIPTION
				"Input 2 fail Trap Enable"
		::= { act3000c01v1Entry 108 }

		-- 1.3.6.1.4.1.10106.3.101291.1.1.109
		act3000c01v1StatusIn1Ext OBJECT-TYPE
			SYNTAX BitFail
			MAX-ACCESS read-only
			STATUS current
			DESCRIPTION
				"Input 1 external fail"
		::= { act3000c01v1Entry 109 }

		-- 1.3.6.1.4.1.10106.3.101291.1.1.110
		act3000c01v1StatusIn1ExtTrapEnable OBJECT-TYPE
			SYNTAX AlarmEnable
			MAX-ACCESS read-write
			STATUS current
			DESCRIPTION
				"Input 1 external fail Trap Enable"
		::= { act3000c01v1Entry 110 }

		-- 1.3.6.1.4.1.10106.3.101291.1.1.111
		act3000c01v1StatusIn2Ext OBJECT-TYPE
			SYNTAX BitFail
			MAX-ACCESS read-only
			STATUS current
			DESCRIPTION
				"Input 2 external fail"
		::= { act3000c01v1Entry 111 }

		-- 1.3.6.1.4.1.10106.3.101291.1.1.112
		act3000c01v1StatusIn2ExtTrapEnable OBJECT-TYPE
			SYNTAX AlarmEnable
			MAX-ACCESS read-write
			STATUS current
			DESCRIPTION
				"Input 2 external fail Trap Enable"
		::= { act3000c01v1Entry 112 }

		-- 1.3.6.1.4.1.10106.3.101291.1.1.113
		act3000c01v1StatusIn1Clip OBJECT-TYPE
			SYNTAX BitFail
			MAX-ACCESS read-only
			STATUS current
			DESCRIPTION
				"Input 1 clipping fail"
		::= { act3000c01v1Entry 113 }

		-- 1.3.6.1.4.1.10106.3.101291.1.1.114
		act3000c01v1StatusIn1ClipTrapEnable OBJECT-TYPE
			SYNTAX AlarmEnable
			MAX-ACCESS read-write
			STATUS current
			DESCRIPTION
				"Input 1 clipping fail Trap Enable"
		::= { act3000c01v1Entry 114 }

		-- 1.3.6.1.4.1.10106.3.101291.1.1.115
		act3000c01v1StatusIn2Clip OBJECT-TYPE
			SYNTAX BitFail
			MAX-ACCESS read-only
			STATUS current
			DESCRIPTION
				"Input 2 clipping fail"
		::= { act3000c01v1Entry 115 }

		-- 1.3.6.1.4.1.10106.3.101291.1.1.116
		act3000c01v1StatusIn2ClipTrapEnable OBJECT-TYPE
			SYNTAX AlarmEnable
			MAX-ACCESS read-write
			STATUS current
			DESCRIPTION
				"Input 2 clipping fail Trap Enable"
		::= { act3000c01v1Entry 116 }

		-- 1.3.6.1.4.1.10106.3.101291.1.1.117
		act3000c01v1SelOut1 OBJECT-TYPE
			SYNTAX ActMapState
			MAX-ACCESS read-only
			STATUS current
			DESCRIPTION
				"Output 1"
		::= { act3000c01v1Entry 117 }

		-- 1.3.6.1.4.1.10106.3.101291.1.1.118
		act3000c01v1SelOut1TrapEnable OBJECT-TYPE
			SYNTAX AlarmEnable
			MAX-ACCESS read-write
			STATUS current
			DESCRIPTION
				"Output 1 Trap Enable"
		::= { act3000c01v1Entry 118 }

		-- 1.3.6.1.4.1.10106.3.101291.1.1.119
		act3000c01v1SelOut2 OBJECT-TYPE
			SYNTAX ActMapState
			MAX-ACCESS read-only
			STATUS current
			DESCRIPTION
				"Output 2"
		::= { act3000c01v1Entry 119 }

		-- 1.3.6.1.4.1.10106.3.101291.1.1.120
		act3000c01v1SelOut2TrapEnable OBJECT-TYPE
			SYNTAX AlarmEnable
			MAX-ACCESS read-write
			STATUS current
			DESCRIPTION
				"Output 2 Trap Enable"
		::= { act3000c01v1Entry 120 }

		-- 1.3.6.1.4.1.10106.3.101291.1.1.121
		act3000c01v1Gpo1Out OBJECT-TYPE
			SYNTAX Bit0Ina1Act
			MAX-ACCESS read-only
			STATUS current
			DESCRIPTION
				"GPO 1"
		::= { act3000c01v1Entry 121 }

		-- 1.3.6.1.4.1.10106.3.101291.1.1.123
		act3000c01v1Gpo2Out OBJECT-TYPE
			SYNTAX Bit0Ina1Act
			MAX-ACCESS read-only
			STATUS current
			DESCRIPTION
				"GPO 2"
		::= { act3000c01v1Entry 123 }

		-- 1.3.6.1.4.1.10106.3.101291.1.1.125
		act3000c01v1Gpi1Stat OBJECT-TYPE
			SYNTAX BitFail
			MAX-ACCESS read-only
			STATUS current
			DESCRIPTION
				"GPI1 status (used in remote control)"
		::= { act3000c01v1Entry 125 }

		-- 1.3.6.1.4.1.10106.3.101291.1.1.126
		act3000c01v1Gpi1StatTrapEnable OBJECT-TYPE
			SYNTAX AlarmEnable
			MAX-ACCESS read-write
			STATUS current
			DESCRIPTION
				"GPI1 status (used in remote control) Trap Enable"
		::= { act3000c01v1Entry 126 }

		-- 1.3.6.1.4.1.10106.3.101291.1.1.127
		act3000c01v1FailSil1l OBJECT-TYPE
			SYNTAX BitFail
			MAX-ACCESS read-only
			STATUS current
			DESCRIPTION
				"Silence in input 1L"
		::= { act3000c01v1Entry 127 }

		-- 1.3.6.1.4.1.10106.3.101291.1.1.128
		act3000c01v1FailSil1lTrapEnable OBJECT-TYPE
			SYNTAX AlarmEnable
			MAX-ACCESS read-write
			STATUS current
			DESCRIPTION
				"Silence in input 1L Trap Enable"
		::= { act3000c01v1Entry 128 }

		-- 1.3.6.1.4.1.10106.3.101291.1.1.129
		act3000c01v1FailOvld1l OBJECT-TYPE
			SYNTAX BitFail
			MAX-ACCESS read-only
			STATUS current
			DESCRIPTION
				"Overload in input 1L"
		::= { act3000c01v1Entry 129 }

		-- 1.3.6.1.4.1.10106.3.101291.1.1.130
		act3000c01v1FailOvld1lTrapEnable OBJECT-TYPE
			SYNTAX AlarmEnable
			MAX-ACCESS read-write
			STATUS current
			DESCRIPTION
				"Overload in input 1L Trap Enable"
		::= { act3000c01v1Entry 130 }

		-- 1.3.6.1.4.1.10106.3.101291.1.1.131
		act3000c01v1FailClip1l OBJECT-TYPE
			SYNTAX BitFail
			MAX-ACCESS read-only
			STATUS current
			DESCRIPTION
				"Clipping in input 1L"
		::= { act3000c01v1Entry 131 }

		-- 1.3.6.1.4.1.10106.3.101291.1.1.132
		act3000c01v1FailClip1lTrapEnable OBJECT-TYPE
			SYNTAX AlarmEnable
			MAX-ACCESS read-write
			STATUS current
			DESCRIPTION
				"Clipping in input 1L Trap Enable"
		::= { act3000c01v1Entry 132 }

		-- 1.3.6.1.4.1.10106.3.101291.1.1.133
		act3000c01v1FailAnti1 OBJECT-TYPE
			SYNTAX BitFail
			MAX-ACCESS read-only
			STATUS current
			DESCRIPTION
				"Antiphase fail in input 1"
		::= { act3000c01v1Entry 133 }

		-- 1.3.6.1.4.1.10106.3.101291.1.1.134
		act3000c01v1FailAnti1TrapEnable OBJECT-TYPE
			SYNTAX AlarmEnable
			MAX-ACCESS read-write
			STATUS current
			DESCRIPTION
				"Antiphase fail in input 1 Trap Enable"
		::= { act3000c01v1Entry 134 }

		-- 1.3.6.1.4.1.10106.3.101291.1.1.135
		act3000c01v1FailSil1r OBJECT-TYPE
			SYNTAX BitFail
			MAX-ACCESS read-only
			STATUS current
			DESCRIPTION
				"Silence in input 1R"
		::= { act3000c01v1Entry 135 }

		-- 1.3.6.1.4.1.10106.3.101291.1.1.136
		act3000c01v1FailSil1rTrapEnable OBJECT-TYPE
			SYNTAX AlarmEnable
			MAX-ACCESS read-write
			STATUS current
			DESCRIPTION
				"Silence in input 1R Trap Enable"
		::= { act3000c01v1Entry 136 }

		-- 1.3.6.1.4.1.10106.3.101291.1.1.137
		act3000c01v1FailOvld1r OBJECT-TYPE
			SYNTAX BitFail
			MAX-ACCESS read-only
			STATUS current
			DESCRIPTION
				"Overload in input 1R"
		::= { act3000c01v1Entry 137 }

		-- 1.3.6.1.4.1.10106.3.101291.1.1.138
		act3000c01v1FailOvld1rTrapEnable OBJECT-TYPE
			SYNTAX AlarmEnable
			MAX-ACCESS read-write
			STATUS current
			DESCRIPTION
				"Overload in input 1R Trap Enable"
		::= { act3000c01v1Entry 138 }

		-- 1.3.6.1.4.1.10106.3.101291.1.1.139
		act3000c01v1FailClip1r OBJECT-TYPE
			SYNTAX BitFail
			MAX-ACCESS read-only
			STATUS current
			DESCRIPTION
				"Clipping in input 1R"
		::= { act3000c01v1Entry 139 }

		-- 1.3.6.1.4.1.10106.3.101291.1.1.140
		act3000c01v1FailClip1rTrapEnable OBJECT-TYPE
			SYNTAX AlarmEnable
			MAX-ACCESS read-write
			STATUS current
			DESCRIPTION
				"Clipping in input 1R Trap Enable"
		::= { act3000c01v1Entry 140 }

		-- 1.3.6.1.4.1.10106.3.101291.1.1.141
		act3000c01v1FailExt1 OBJECT-TYPE
			SYNTAX BitFail
			MAX-ACCESS read-only
			STATUS current
			DESCRIPTION
				"External fail over input 1"
		::= { act3000c01v1Entry 141 }

		-- 1.3.6.1.4.1.10106.3.101291.1.1.142
		act3000c01v1FailExt1TrapEnable OBJECT-TYPE
			SYNTAX AlarmEnable
			MAX-ACCESS read-write
			STATUS current
			DESCRIPTION
				"External fail over input 1 Trap Enable"
		::= { act3000c01v1Entry 142 }

		-- 1.3.6.1.4.1.10106.3.101291.1.1.143
		act3000c01v1FailSil2l OBJECT-TYPE
			SYNTAX BitFail
			MAX-ACCESS read-only
			STATUS current
			DESCRIPTION
				"Silence in input 2L"
		::= { act3000c01v1Entry 143 }

		-- 1.3.6.1.4.1.10106.3.101291.1.1.144
		act3000c01v1FailSil2lTrapEnable OBJECT-TYPE
			SYNTAX AlarmEnable
			MAX-ACCESS read-write
			STATUS current
			DESCRIPTION
				"Silence in input 2L Trap Enable"
		::= { act3000c01v1Entry 144 }

		-- 1.3.6.1.4.1.10106.3.101291.1.1.145
		act3000c01v1FailOvld2l OBJECT-TYPE
			SYNTAX BitFail
			MAX-ACCESS read-only
			STATUS current
			DESCRIPTION
				"Overload in input 2L"
		::= { act3000c01v1Entry 145 }

		-- 1.3.6.1.4.1.10106.3.101291.1.1.146
		act3000c01v1FailOvld2lTrapEnable OBJECT-TYPE
			SYNTAX AlarmEnable
			MAX-ACCESS read-write
			STATUS current
			DESCRIPTION
				"Overload in input 2L Trap Enable"
		::= { act3000c01v1Entry 146 }

		-- 1.3.6.1.4.1.10106.3.101291.1.1.147
		act3000c01v1FailClip2l OBJECT-TYPE
			SYNTAX BitFail
			MAX-ACCESS read-only
			STATUS current
			DESCRIPTION
				"Clipping in input 2L"
		::= { act3000c01v1Entry 147 }

		-- 1.3.6.1.4.1.10106.3.101291.1.1.148
		act3000c01v1FailClip2lTrapEnable OBJECT-TYPE
			SYNTAX AlarmEnable
			MAX-ACCESS read-write
			STATUS current
			DESCRIPTION
				"Clipping in input 2L Trap Enable"
		::= { act3000c01v1Entry 148 }

		-- 1.3.6.1.4.1.10106.3.101291.1.1.149
		act3000c01v1FailAnti2 OBJECT-TYPE
			SYNTAX BitFail
			MAX-ACCESS read-only
			STATUS current
			DESCRIPTION
				"Antiphase fail in input 2"
		::= { act3000c01v1Entry 149 }

		-- 1.3.6.1.4.1.10106.3.101291.1.1.150
		act3000c01v1FailAnti2TrapEnable OBJECT-TYPE
			SYNTAX AlarmEnable
			MAX-ACCESS read-write
			STATUS current
			DESCRIPTION
				"Antiphase fail in input 2 Trap Enable"
		::= { act3000c01v1Entry 150 }

		-- 1.3.6.1.4.1.10106.3.101291.1.1.151
		act3000c01v1FailSil2r OBJECT-TYPE
			SYNTAX BitFail
			MAX-ACCESS read-only
			STATUS current
			DESCRIPTION
				"Silence in input 2R"
		::= { act3000c01v1Entry 151 }

		-- 1.3.6.1.4.1.10106.3.101291.1.1.152
		act3000c01v1FailSil2rTrapEnable OBJECT-TYPE
			SYNTAX AlarmEnable
			MAX-ACCESS read-write
			STATUS current
			DESCRIPTION
				"Silence in input 2R Trap Enable"
		::= { act3000c01v1Entry 152 }

		-- 1.3.6.1.4.1.10106.3.101291.1.1.153
		act3000c01v1FailOvld2r OBJECT-TYPE
			SYNTAX BitFail
			MAX-ACCESS read-only
			STATUS current
			DESCRIPTION
				"Overload in input 2R"
		::= { act3000c01v1Entry 153 }

		-- 1.3.6.1.4.1.10106.3.101291.1.1.154
		act3000c01v1FailOvld2rTrapEnable OBJECT-TYPE
			SYNTAX AlarmEnable
			MAX-ACCESS read-write
			STATUS current
			DESCRIPTION
				"Overload in input 2R Trap Enable"
		::= { act3000c01v1Entry 154 }

		-- 1.3.6.1.4.1.10106.3.101291.1.1.155
		act3000c01v1FailClip2r OBJECT-TYPE
			SYNTAX BitFail
			MAX-ACCESS read-only
			STATUS current
			DESCRIPTION
				"Clipping in input 2R"
		::= { act3000c01v1Entry 155 }

		-- 1.3.6.1.4.1.10106.3.101291.1.1.156
		act3000c01v1FailClip2rTrapEnable OBJECT-TYPE
			SYNTAX AlarmEnable
			MAX-ACCESS read-write
			STATUS current
			DESCRIPTION
				"Clipping in input 2R Trap Enable"
		::= { act3000c01v1Entry 156 }

		-- 1.3.6.1.4.1.10106.3.101291.1.1.157
		act3000c01v1FailExt2 OBJECT-TYPE
			SYNTAX BitFail
			MAX-ACCESS read-only
			STATUS current
			DESCRIPTION
				"External fail over input 2"
		::= { act3000c01v1Entry 157 }

		-- 1.3.6.1.4.1.10106.3.101291.1.1.158
		act3000c01v1FailExt2TrapEnable OBJECT-TYPE
			SYNTAX AlarmEnable
			MAX-ACCESS read-write
			STATUS current
			DESCRIPTION
				"External fail over input 2 Trap Enable"
		::= { act3000c01v1Entry 158 }

		-- 1.3.6.1.4.1.10106.3.101291.1.1.159
		act3000c01v1CurrentSmooth OBJECT-TYPE
			SYNTAX BitFail
			MAX-ACCESS read-only
			STATUS current
			DESCRIPTION
				"Currently smooth delay"
		::= { act3000c01v1Entry 159 }

		-- 1.3.6.1.4.1.10106.3.101291.1.1.161
		act3000c01v1SerialNo OBJECT-TYPE
			SYNTAX SerialNo
			MAX-ACCESS read-only
			STATUS current
			DESCRIPTION
				"Serial number"
		::= { act3000c01v1Entry 161 }

		-- 1.3.6.1.4.1.10106.3.416301
		hvd2000c01v1 OBJECT IDENTIFIER ::= { albalaProducts 416301 }

		-- 1.3.6.1.4.1.10106.3.416301.1
		hvd2000c01v1Table  OBJECT-TYPE
			SYNTAX SEQUENCE OF Hvd2000c01v1Entry
			MAX-ACCESS not-accessible
			STATUS current
			DESCRIPTION
				"Module  HVD2000C01V1 Table"
			::= { hvd2000c01v1 1 }

		-- 1.3.6.1.4.1.10106.3.416301.1.1
		hvd2000c01v1Entry  OBJECT-TYPE
			SYNTAX Hvd2000c01v1Entry
			MAX-ACCESS not-accessible
			STATUS current
			DESCRIPTION
				"Module HVD2000C01V1 Entry"
			INDEX { hvd2000c01v1Index }
			::= { hvd2000c01v1Table 1 }

			Hvd2000c01v1Entry ::=
			SEQUENCE {
				hvd2000c01v1Index
				ModuleIndex,
				hvd2000c01v1NoSig
				BitFail,
				hvd2000c01v1NoSigTrapEnable
				AlarmEnable,
				hvd2000c01v1Unlock
				BitFail,
				hvd2000c01v1UnlockTrapEnable
				AlarmEnable,
				hvd2000c01v1Hd
				Bit0Sd1Hd,
				hvd2000c01v1SerialNo
				SerialNo
			 }

		-- 1.3.6.1.4.1.10106.3.101291.1.1.1
		hvd2000c01v1Index OBJECT-TYPE
			SYNTAX ModuleIndex
			MAX-ACCESS read-only
			STATUS current
			DESCRIPTION
				"Index of HVD2000C01V1 Table"
		::= { hvd2000c01v1Entry 1 }

		-- 1.3.6.1.4.1.10106.3.101291.1.1.3
		hvd2000c01v1NoSig OBJECT-TYPE
			SYNTAX BitFail
			MAX-ACCESS read-only
			STATUS current
			DESCRIPTION
				"Input signal status"
		::= { hvd2000c01v1Entry 3 }

		-- 1.3.6.1.4.1.10106.3.101291.1.1.4
		hvd2000c01v1NoSigTrapEnable OBJECT-TYPE
			SYNTAX AlarmEnable
			MAX-ACCESS read-write
			STATUS current
			DESCRIPTION
				"Input signal status Trap Enable"
		::= { hvd2000c01v1Entry 4 }

		-- 1.3.6.1.4.1.10106.3.101291.1.1.5
		hvd2000c01v1Unlock OBJECT-TYPE
			SYNTAX BitFail
			MAX-ACCESS read-only
			STATUS current
			DESCRIPTION
				"Indicates signal unlock fail"
		::= { hvd2000c01v1Entry 5 }

		-- 1.3.6.1.4.1.10106.3.101291.1.1.6
		hvd2000c01v1UnlockTrapEnable OBJECT-TYPE
			SYNTAX AlarmEnable
			MAX-ACCESS read-write
			STATUS current
			DESCRIPTION
				"Indicates signal unlock fail Trap Enable"
		::= { hvd2000c01v1Entry 6 }

		-- 1.3.6.1.4.1.10106.3.101291.1.1.7
		hvd2000c01v1Hd OBJECT-TYPE
			SYNTAX Bit0Sd1Hd
			MAX-ACCESS read-only
			STATUS current
			DESCRIPTION
				"Indicates the SDI signal type"
		::= { hvd2000c01v1Entry 7 }

		-- 1.3.6.1.4.1.10106.3.101291.1.1.9
		hvd2000c01v1SerialNo OBJECT-TYPE
			SYNTAX SerialNo
			MAX-ACCESS read-only
			STATUS current
			DESCRIPTION
				"Serial number"
		::= { hvd2000c01v1Entry 9 }

		-- 1.3.6.1.4.1.10106.3.420401
		kbd3160c02v1 OBJECT IDENTIFIER ::= { albalaProducts 420401 }

		-- 1.3.6.1.4.1.10106.3.420401.1
		kbd3160c02v1Table  OBJECT-TYPE
			SYNTAX SEQUENCE OF Kbd3160c02v1Entry
			MAX-ACCESS not-accessible
			STATUS current
			DESCRIPTION
				"Module  KBD3160C02V1 Table"
			::= { kbd3160c02v1 1 }

		-- 1.3.6.1.4.1.10106.3.420401.1.1
		kbd3160c02v1Entry  OBJECT-TYPE
			SYNTAX Kbd3160c02v1Entry
			MAX-ACCESS not-accessible
			STATUS current
			DESCRIPTION
				"Module KBD3160C02V1 Entry"
			INDEX { kbd3160c02v1Index }
			::= { kbd3160c02v1Table 1 }

			Kbd3160c02v1Entry ::=
			SEQUENCE {
				kbd3160c02v1Index
				ModuleIndex,
				kbd3160c02v1BeepEna
				Bit0No1Yes,
				kbd3160c02v1Brightness
				Brightness,
				kbd3160c02v1Gpo1
				Bit0Ina1Act,
				kbd3160c02v1Gpo2
				Bit0Ina1Act,
				kbd3160c02v1Gpo3
				Bit0Ina1Act,
				kbd3160c02v1Gpo4
				Bit0Ina1Act,
				kbd3160c02v1Gpo5
				Bit0Ina1Act,
				kbd3160c02v1Gpo6
				Bit0Ina1Act,
				kbd3160c02v1Gpo7
				Bit0Ina1Act,
				kbd3160c02v1Gpo8
				Bit0Ina1Act,
				kbd3160c02v1Gpo9
				Bit0Ina1Act,
				kbd3160c02v1Gpo10
				Bit0Ina1Act,
				kbd3160c02v1Gpo11
				Bit0Ina1Act,
				kbd3160c02v1Gpo12
				Bit0Ina1Act,
				kbd3160c02v1Gpo13
				Bit0Ina1Act,
				kbd3160c02v1Gpo14
				Bit0Ina1Act,
				kbd3160c02v1Gpo15
				Bit0Ina1Act,
				kbd3160c02v1Gpo16
				Bit0Ina1Act,
				kbd3160c02v1Gpi1
				Bit0Ina1Act,
				kbd3160c02v1Gpi2
				Bit0Ina1Act,
				kbd3160c02v1Gpi3
				Bit0Ina1Act,
				kbd3160c02v1Gpi4
				Bit0Ina1Act,
				kbd3160c02v1Gpi5
				Bit0Ina1Act,
				kbd3160c02v1Gpi6
				Bit0Ina1Act,
				kbd3160c02v1Gpi7
				Bit0Ina1Act,
				kbd3160c02v1Gpi8
				Bit0Ina1Act,
				kbd3160c02v1Gpi9
				Bit0Ina1Act,
				kbd3160c02v1Gpi10
				Bit0Ina1Act,
				kbd3160c02v1Gpi11
				Bit0Ina1Act,
				kbd3160c02v1Gpi12
				Bit0Ina1Act,
				kbd3160c02v1Gpi13
				Bit0Ina1Act,
				kbd3160c02v1Gpi14
				Bit0Ina1Act,
				kbd3160c02v1Gpi15
				Bit0Ina1Act,
				kbd3160c02v1Gpi16
				Bit0Ina1Act,
				kbd3160c02v1Psu0Fail
				BitFail,
				kbd3160c02v1Psu1Fail
				BitFail,
				kbd3160c02v1SerialNo
				SerialNo
			 }

		-- 1.3.6.1.4.1.10106.3.101291.1.1.1
		kbd3160c02v1Index OBJECT-TYPE
			SYNTAX ModuleIndex
			MAX-ACCESS read-only
			STATUS current
			DESCRIPTION
				"Index of KBD3160C02V1 Table"
		::= { kbd3160c02v1Entry 1 }

		-- 1.3.6.1.4.1.10106.3.101291.1.1.3
		kbd3160c02v1BeepEna OBJECT-TYPE
			SYNTAX Bit0No1Yes
			MAX-ACCESS read-write
			STATUS current
			DESCRIPTION
				"Allows that the keys make a beep when pressed or not"
		::= { kbd3160c02v1Entry 3 }

		-- 1.3.6.1.4.1.10106.3.101291.1.1.5
		kbd3160c02v1Brightness OBJECT-TYPE
			SYNTAX Brightness
			MAX-ACCESS read-write
			STATUS current
			DESCRIPTION
				"Allows changing key brightness"
		::= { kbd3160c02v1Entry 5 }

		-- 1.3.6.1.4.1.10106.3.101291.1.1.7
		kbd3160c02v1Gpo1 OBJECT-TYPE
			SYNTAX Bit0Ina1Act
			MAX-ACCESS read-write
			STATUS current
			DESCRIPTION
				"Allows control of GPO1"
		::= { kbd3160c02v1Entry 7 }

		-- 1.3.6.1.4.1.10106.3.101291.1.1.9
		kbd3160c02v1Gpo2 OBJECT-TYPE
			SYNTAX Bit0Ina1Act
			MAX-ACCESS read-write
			STATUS current
			DESCRIPTION
				"Allows control of GPO2"
		::= { kbd3160c02v1Entry 9 }

		-- 1.3.6.1.4.1.10106.3.101291.1.1.11
		kbd3160c02v1Gpo3 OBJECT-TYPE
			SYNTAX Bit0Ina1Act
			MAX-ACCESS read-write
			STATUS current
			DESCRIPTION
				"Allows control of GPO3"
		::= { kbd3160c02v1Entry 11 }

		-- 1.3.6.1.4.1.10106.3.101291.1.1.13
		kbd3160c02v1Gpo4 OBJECT-TYPE
			SYNTAX Bit0Ina1Act
			MAX-ACCESS read-write
			STATUS current
			DESCRIPTION
				"Allows control of GPO4"
		::= { kbd3160c02v1Entry 13 }

		-- 1.3.6.1.4.1.10106.3.101291.1.1.15
		kbd3160c02v1Gpo5 OBJECT-TYPE
			SYNTAX Bit0Ina1Act
			MAX-ACCESS read-write
			STATUS current
			DESCRIPTION
				"Allows control of GPO5"
		::= { kbd3160c02v1Entry 15 }

		-- 1.3.6.1.4.1.10106.3.101291.1.1.17
		kbd3160c02v1Gpo6 OBJECT-TYPE
			SYNTAX Bit0Ina1Act
			MAX-ACCESS read-write
			STATUS current
			DESCRIPTION
				"Allows control of GPO6"
		::= { kbd3160c02v1Entry 17 }

		-- 1.3.6.1.4.1.10106.3.101291.1.1.19
		kbd3160c02v1Gpo7 OBJECT-TYPE
			SYNTAX Bit0Ina1Act
			MAX-ACCESS read-write
			STATUS current
			DESCRIPTION
				"Allows control of GPO7"
		::= { kbd3160c02v1Entry 19 }

		-- 1.3.6.1.4.1.10106.3.101291.1.1.21
		kbd3160c02v1Gpo8 OBJECT-TYPE
			SYNTAX Bit0Ina1Act
			MAX-ACCESS read-write
			STATUS current
			DESCRIPTION
				"Allows control of GPO8"
		::= { kbd3160c02v1Entry 21 }

		-- 1.3.6.1.4.1.10106.3.101291.1.1.23
		kbd3160c02v1Gpo9 OBJECT-TYPE
			SYNTAX Bit0Ina1Act
			MAX-ACCESS read-write
			STATUS current
			DESCRIPTION
				"Allows control of GPO9"
		::= { kbd3160c02v1Entry 23 }

		-- 1.3.6.1.4.1.10106.3.101291.1.1.25
		kbd3160c02v1Gpo10 OBJECT-TYPE
			SYNTAX Bit0Ina1Act
			MAX-ACCESS read-write
			STATUS current
			DESCRIPTION
				"Allows control of GPO10"
		::= { kbd3160c02v1Entry 25 }

		-- 1.3.6.1.4.1.10106.3.101291.1.1.27
		kbd3160c02v1Gpo11 OBJECT-TYPE
			SYNTAX Bit0Ina1Act
			MAX-ACCESS read-write
			STATUS current
			DESCRIPTION
				"Allows control of GPO11"
		::= { kbd3160c02v1Entry 27 }

		-- 1.3.6.1.4.1.10106.3.101291.1.1.29
		kbd3160c02v1Gpo12 OBJECT-TYPE
			SYNTAX Bit0Ina1Act
			MAX-ACCESS read-write
			STATUS current
			DESCRIPTION
				"Allows control of GPO12"
		::= { kbd3160c02v1Entry 29 }

		-- 1.3.6.1.4.1.10106.3.101291.1.1.31
		kbd3160c02v1Gpo13 OBJECT-TYPE
			SYNTAX Bit0Ina1Act
			MAX-ACCESS read-write
			STATUS current
			DESCRIPTION
				"Allows control of GPO13"
		::= { kbd3160c02v1Entry 31 }

		-- 1.3.6.1.4.1.10106.3.101291.1.1.33
		kbd3160c02v1Gpo14 OBJECT-TYPE
			SYNTAX Bit0Ina1Act
			MAX-ACCESS read-write
			STATUS current
			DESCRIPTION
				"Allows control of GPO14"
		::= { kbd3160c02v1Entry 33 }

		-- 1.3.6.1.4.1.10106.3.101291.1.1.35
		kbd3160c02v1Gpo15 OBJECT-TYPE
			SYNTAX Bit0Ina1Act
			MAX-ACCESS read-write
			STATUS current
			DESCRIPTION
				"Allows control of GPO15"
		::= { kbd3160c02v1Entry 35 }

		-- 1.3.6.1.4.1.10106.3.101291.1.1.37
		kbd3160c02v1Gpo16 OBJECT-TYPE
			SYNTAX Bit0Ina1Act
			MAX-ACCESS read-write
			STATUS current
			DESCRIPTION
				"Allows control of GPO16"
		::= { kbd3160c02v1Entry 37 }

		-- 1.3.6.1.4.1.10106.3.101291.1.1.39
		kbd3160c02v1Gpi1 OBJECT-TYPE
			SYNTAX Bit0Ina1Act
			MAX-ACCESS read-only
			STATUS current
			DESCRIPTION
				"GPI1 status"
		::= { kbd3160c02v1Entry 39 }

		-- 1.3.6.1.4.1.10106.3.101291.1.1.41
		kbd3160c02v1Gpi2 OBJECT-TYPE
			SYNTAX Bit0Ina1Act
			MAX-ACCESS read-only
			STATUS current
			DESCRIPTION
				"GPI2 status"
		::= { kbd3160c02v1Entry 41 }

		-- 1.3.6.1.4.1.10106.3.101291.1.1.43
		kbd3160c02v1Gpi3 OBJECT-TYPE
			SYNTAX Bit0Ina1Act
			MAX-ACCESS read-only
			STATUS current
			DESCRIPTION
				"GPI3 status"
		::= { kbd3160c02v1Entry 43 }

		-- 1.3.6.1.4.1.10106.3.101291.1.1.45
		kbd3160c02v1Gpi4 OBJECT-TYPE
			SYNTAX Bit0Ina1Act
			MAX-ACCESS read-only
			STATUS current
			DESCRIPTION
				"GPI4 status"
		::= { kbd3160c02v1Entry 45 }

		-- 1.3.6.1.4.1.10106.3.101291.1.1.47
		kbd3160c02v1Gpi5 OBJECT-TYPE
			SYNTAX Bit0Ina1Act
			MAX-ACCESS read-only
			STATUS current
			DESCRIPTION
				"GPI5 status"
		::= { kbd3160c02v1Entry 47 }

		-- 1.3.6.1.4.1.10106.3.101291.1.1.49
		kbd3160c02v1Gpi6 OBJECT-TYPE
			SYNTAX Bit0Ina1Act
			MAX-ACCESS read-only
			STATUS current
			DESCRIPTION
				"GPI6 status"
		::= { kbd3160c02v1Entry 49 }

		-- 1.3.6.1.4.1.10106.3.101291.1.1.51
		kbd3160c02v1Gpi7 OBJECT-TYPE
			SYNTAX Bit0Ina1Act
			MAX-ACCESS read-only
			STATUS current
			DESCRIPTION
				"GPI7 status"
		::= { kbd3160c02v1Entry 51 }

		-- 1.3.6.1.4.1.10106.3.101291.1.1.53
		kbd3160c02v1Gpi8 OBJECT-TYPE
			SYNTAX Bit0Ina1Act
			MAX-ACCESS read-only
			STATUS current
			DESCRIPTION
				"GPI8 status"
		::= { kbd3160c02v1Entry 53 }

		-- 1.3.6.1.4.1.10106.3.101291.1.1.55
		kbd3160c02v1Gpi9 OBJECT-TYPE
			SYNTAX Bit0Ina1Act
			MAX-ACCESS read-only
			STATUS current
			DESCRIPTION
				"GPI9 status"
		::= { kbd3160c02v1Entry 55 }

		-- 1.3.6.1.4.1.10106.3.101291.1.1.57
		kbd3160c02v1Gpi10 OBJECT-TYPE
			SYNTAX Bit0Ina1Act
			MAX-ACCESS read-only
			STATUS current
			DESCRIPTION
				"GPI10 status"
		::= { kbd3160c02v1Entry 57 }

		-- 1.3.6.1.4.1.10106.3.101291.1.1.59
		kbd3160c02v1Gpi11 OBJECT-TYPE
			SYNTAX Bit0Ina1Act
			MAX-ACCESS read-only
			STATUS current
			DESCRIPTION
				"GPI11 status"
		::= { kbd3160c02v1Entry 59 }

		-- 1.3.6.1.4.1.10106.3.101291.1.1.61
		kbd3160c02v1Gpi12 OBJECT-TYPE
			SYNTAX Bit0Ina1Act
			MAX-ACCESS read-only
			STATUS current
			DESCRIPTION
				"GPI12 status"
		::= { kbd3160c02v1Entry 61 }

		-- 1.3.6.1.4.1.10106.3.101291.1.1.63
		kbd3160c02v1Gpi13 OBJECT-TYPE
			SYNTAX Bit0Ina1Act
			MAX-ACCESS read-only
			STATUS current
			DESCRIPTION
				"GPI13 status"
		::= { kbd3160c02v1Entry 63 }

		-- 1.3.6.1.4.1.10106.3.101291.1.1.65
		kbd3160c02v1Gpi14 OBJECT-TYPE
			SYNTAX Bit0Ina1Act
			MAX-ACCESS read-only
			STATUS current
			DESCRIPTION
				"GPI14 status"
		::= { kbd3160c02v1Entry 65 }

		-- 1.3.6.1.4.1.10106.3.101291.1.1.67
		kbd3160c02v1Gpi15 OBJECT-TYPE
			SYNTAX Bit0Ina1Act
			MAX-ACCESS read-only
			STATUS current
			DESCRIPTION
				"GPI15 status"
		::= { kbd3160c02v1Entry 67 }

		-- 1.3.6.1.4.1.10106.3.101291.1.1.69
		kbd3160c02v1Gpi16 OBJECT-TYPE
			SYNTAX Bit0Ina1Act
			MAX-ACCESS read-only
			STATUS current
			DESCRIPTION
				"GPI16 status"
		::= { kbd3160c02v1Entry 69 }

		-- 1.3.6.1.4.1.10106.3.101291.1.1.71
		kbd3160c02v1Psu0Fail OBJECT-TYPE
			SYNTAX BitFail
			MAX-ACCESS read-only
			STATUS current
			DESCRIPTION
				"Indicates fail in power supply 1"
		::= { kbd3160c02v1Entry 71 }

		-- 1.3.6.1.4.1.10106.3.101291.1.1.73
		kbd3160c02v1Psu1Fail OBJECT-TYPE
			SYNTAX BitFail
			MAX-ACCESS read-only
			STATUS current
			DESCRIPTION
				"Indicates fail in power supply 2"
		::= { kbd3160c02v1Entry 73 }

		-- 1.3.6.1.4.1.10106.3.101291.1.1.75
		kbd3160c02v1SerialNo OBJECT-TYPE
			SYNTAX SerialNo
			MAX-ACCESS read-only
			STATUS current
			DESCRIPTION
				"Serial number"
		::= { kbd3160c02v1Entry 75 }

		-- 1.3.6.1.4.1.10106.3.422601
		tsa3000c01v1 OBJECT IDENTIFIER ::= { albalaProducts 422601 }

		-- 1.3.6.1.4.1.10106.3.422601.1
		tsa3000c01v1Table  OBJECT-TYPE
			SYNTAX SEQUENCE OF Tsa3000c01v1Entry
			MAX-ACCESS not-accessible
			STATUS current
			DESCRIPTION
				"Module  TSA3000C01V1 Table"
			::= { tsa3000c01v1 1 }

		-- 1.3.6.1.4.1.10106.3.422601.1.1
		tsa3000c01v1Entry  OBJECT-TYPE
			SYNTAX Tsa3000c01v1Entry
			MAX-ACCESS not-accessible
			STATUS current
			DESCRIPTION
				"Module TSA3000C01V1 Entry"
			INDEX { tsa3000c01v1Index }
			::= { tsa3000c01v1Table 1 }

			Tsa3000c01v1Entry ::=
			SEQUENCE {
				tsa3000c01v1Index
				ModuleIndex,
				tsa3000c01v1Mode
				ChgOverMode2,
				tsa3000c01v1ModeTrapEnable
				AlarmEnable,
				tsa3000c01v1NullPckRtp
				Bit0No1Yes,
				tsa3000c01v1NarrowPllBw
				Bit0No1Yes,
				tsa3000c01v1Buzzer
				BitMask,
				tsa3000c01v1GpioMode
				GpioModeB,
				tsa3000c01v1InputStChange
				Bit0No1Yes,
				tsa3000c01v1InputChange
				Bit0No1Yes,
				tsa3000c01v1EnaAsi1
				BitMask,
				tsa3000c01v1EnaAsi2
				BitMask,
				tsa3000c01v1EnaIp1
				BitMask,
				tsa3000c01v1EnaIp2
				BitMask,
				tsa3000c01v1SelectedInput
				GatewayInput3,
				tsa3000c01v1SelectedInputTrapEnable
				AlarmEnable,
				tsa3000c01v1PingEnable1
				Bit0No1Yes,
				tsa3000c01v1IpLinkFailEn
				Bit0No1Yes,
				tsa3000c01v1IpDestFailEn
				Bit0No1Yes,
				tsa3000c01v1MaxTimeOut
				TimeX1Ms1,
				tsa3000c01v1StatReset
				Bit0No1Yes,
				tsa3000c01v1StatSel
				Bit0Ipm1Ipr,
				tsa3000c01v1StatMode
				Bit01s1Total,
				tsa3000c01v1IgmpVersion
				Bit0V21V3,
				tsa3000c01v1EthMode
				EthMode,
				tsa3000c01v1PckDelAsiIn1
				DelayPacket1,
				tsa3000c01v1PckDelAsiIn2
				DelayPacket1,
				tsa3000c01v1PckDelIpIn1
				DelayPacket1,
				tsa3000c01v1PckDelIpIn2
				DelayPacket1,
				tsa3000c01v1AsiIn1Prior0
				Uint2,
				tsa3000c01v1AsiIn2Prior0
				Uint2,
				tsa3000c01v1IpIn1Prior0
				Uint2,
				tsa3000c01v1IpIn2Prior0
				Uint2,
				tsa3000c01v1BitrateEn
				Bit0No1Yes,
				tsa3000c01v1Bitrate
				BitrateControl,
				tsa3000c01v1FilterEn
				Bit0Dis1Ena,
				tsa3000c01v1PatPidsEn
				Bit0Dis1Ena,
				tsa3000c01v1CatPidsEn
				Bit0Dis1Ena,
				tsa3000c01v1PmtPrgmEn
				Bit0Dis1Ena,
				tsa3000c01v1RsrvedPidsEn
				Bit0Dis1Ena,
				tsa3000c01v1NullPckEn
				Bit0Dis1Ena,
				tsa3000c01v1InvertFilter
				Bit0Pass1Rem,
				tsa3000c01v1PmtPrgmEn0
				Bit0No1Yes,
				tsa3000c01v1PmtPrgmEn1
				Bit0No1Yes,
				tsa3000c01v1PmtPrgmEn2
				Bit0No1Yes,
				tsa3000c01v1PmtPrgmEn3
				Bit0No1Yes,
				tsa3000c01v1PmtPrgmEn4
				Bit0No1Yes,
				tsa3000c01v1PmtPrgmEn5
				Bit0No1Yes,
				tsa3000c01v1PmtPrgmEn6
				Bit0No1Yes,
				tsa3000c01v1PmtPrgmEn7
				Bit0No1Yes,
				tsa3000c01v1PmtPrgmEn8
				Bit0No1Yes,
				tsa3000c01v1PmtPrgmEn9
				Bit0No1Yes,
				tsa3000c01v1PmtPrgmEn10
				Bit0No1Yes,
				tsa3000c01v1PmtPrgmEn11
				Bit0No1Yes,
				tsa3000c01v1PmtPrgmEn12
				Bit0No1Yes,
				tsa3000c01v1PmtPrgmEn13
				Bit0No1Yes,
				tsa3000c01v1PmtPrgmEn14
				Bit0No1Yes,
				tsa3000c01v1PmtPrgmEn15
				Bit0No1Yes,
				tsa3000c01v1PidPacketEn0
				Bit0No1Yes,
				tsa3000c01v1PidPacketEn1
				Bit0No1Yes,
				tsa3000c01v1PidPacketEn2
				Bit0No1Yes,
				tsa3000c01v1PidPacketEn3
				Bit0No1Yes,
				tsa3000c01v1PidPacketEn4
				Bit0No1Yes,
				tsa3000c01v1PidPacketEn5
				Bit0No1Yes,
				tsa3000c01v1PidPacketEn6
				Bit0No1Yes,
				tsa3000c01v1PidPacketEn7
				Bit0No1Yes,
				tsa3000c01v1PidPacketEn8
				Bit0No1Yes,
				tsa3000c01v1PidPacketEn9
				Bit0No1Yes,
				tsa3000c01v1PidPacketEn10
				Bit0No1Yes,
				tsa3000c01v1PidPacketEn11
				Bit0No1Yes,
				tsa3000c01v1PidPacketEn12
				Bit0No1Yes,
				tsa3000c01v1PidPacketEn13
				Bit0No1Yes,
				tsa3000c01v1PidPacketEn14
				Bit0No1Yes,
				tsa3000c01v1PidPacketEn15
				Bit0No1Yes,
				tsa3000c01v1ActivePreset
				Preset16Active,
				tsa3000c01v1LoadPreset
				Preset16Load,
				tsa3000c01v1SavePreset
				Preset16Save,
				tsa3000c01v1Str1UipDAdd3
				Uint8,
				tsa3000c01v1Str1UipDAdd2
				Uint8,
				tsa3000c01v1Str1UipDAdd1
				Uint8,
				tsa3000c01v1Str1UipDAdd0
				Uint8,
				tsa3000c01v1Str1MipDAdd3
				Uint8,
				tsa3000c01v1Str1MipDAdd2
				Uint8,
				tsa3000c01v1Str1MipDAdd1
				Uint8,
				tsa3000c01v1Str1MipDAdd0
				Uint8,
				tsa3000c01v1Str1DPort
				Uint16,
				tsa3000c01v1Str1FecEna
				Bit0No1Yes,
				tsa3000c01v1Str1MulticEna
				IpaTxMode,
				tsa3000c01v1VlanRx1Enable
				Bit0No1Yes,
				tsa3000c01v1VlanRx1Id
				Uint12,
				tsa3000c01v1Str2UipDAdd3
				Uint8,
				tsa3000c01v1Str2UipDAdd2
				Uint8,
				tsa3000c01v1Str2UipDAdd1
				Uint8,
				tsa3000c01v1Str2UipDAdd0
				Uint8,
				tsa3000c01v1Str2MipDAdd3
				Uint8,
				tsa3000c01v1Str2MipDAdd2
				Uint8,
				tsa3000c01v1Str2MipDAdd1
				Uint8,
				tsa3000c01v1Str2MipDAdd0
				Uint8,
				tsa3000c01v1Str2DPort
				Uint16,
				tsa3000c01v1Str2FecEna
				Bit0No1Yes,
				tsa3000c01v1Str2MulticEna
				IpaTxMode,
				tsa3000c01v1VlanRx2Enable
				Bit0No1Yes,
				tsa3000c01v1VlanRx2Id
				Uint12,
				tsa3000c01v1LocalIpAdd3
				Uint8,
				tsa3000c01v1LocalIpAdd2
				Uint8,
				tsa3000c01v1LocalIpAdd1
				Uint8,
				tsa3000c01v1LocalIpAdd0
				Uint8,
				tsa3000c01v1LocalIpMask3
				Uint8,
				tsa3000c01v1LocalIpMask2
				Uint8,
				tsa3000c01v1LocalIpMask1
				Uint8,
				tsa3000c01v1LocalIpMask0
				Uint8,
				tsa3000c01v1LocalIpGway3
				Uint8,
				tsa3000c01v1LocalIpGway2
				Uint8,
				tsa3000c01v1LocalIpGway1
				Uint8,
				tsa3000c01v1LocalIpGway0
				Uint8,
				tsa3000c01v1Tx1UniEna
				Bit0No1Yes,
				tsa3000c01v1Tx1MultiEna
				IpaTxMode,
				tsa3000c01v1Tx1UipAdd3
				Uint8,
				tsa3000c01v1Tx1UipAdd2
				Uint8,
				tsa3000c01v1Tx1UipAdd1
				Uint8,
				tsa3000c01v1Tx1UipAdd0
				Uint8,
				tsa3000c01v1Tx1MipAdd3
				Uint8,
				tsa3000c01v1Tx1MipAdd2
				Uint8,
				tsa3000c01v1Tx1MipAdd1
				Uint8,
				tsa3000c01v1Tx1MipAdd0
				Uint8,
				tsa3000c01v1Tx1SPort
				Uint16,
				tsa3000c01v1Tx1DPort
				Uint16,
				tsa3000c01v1VlanTxEnable1
				Bit0No1Yes,
				tsa3000c01v1VlanTxPrior1
				Uint3,
				tsa3000c01v1VlanTxId1
				Uint12,
				tsa3000c01v1Tx1LParam
				Uint5,
				tsa3000c01v1Tx1FecMode
				FecMode,
				tsa3000c01v1Tx1DParam
				Uint5,
				tsa3000c01v1Tx1TspkInIppk
				Uint3,
				tsa3000c01v1Tx1RowDelay
				Uint5,
				tsa3000c01v1Tx1ColDelay
				Uint8,
				tsa3000c01v1LowCost1
				Bit0No1Yes,
				tsa3000c01v1HighReliab1
				Bit0No1Yes,
				tsa3000c01v1HighThroughp1
				Bit0No1Yes,
				tsa3000c01v1LowDelay1
				Bit0No1Yes,
				tsa3000c01v1Precedence1
				IpaPrecedence,
				tsa3000c01v1Ttl1
				Uint8,
				tsa3000c01v1Str1IgmFAdd3
				Uint8,
				tsa3000c01v1Str1IgmFAdd2
				Uint8,
				tsa3000c01v1Str1IgmFAdd1
				Uint8,
				tsa3000c01v1Str1IgmFAdd0
				Uint8,
				tsa3000c01v1Str2IgmFAdd3
				Uint8,
				tsa3000c01v1Str2IgmFAdd2
				Uint8,
				tsa3000c01v1Str2IgmFAdd1
				Uint8,
				tsa3000c01v1Str2IgmFAdd0
				Uint8,
				tsa3000c01v1PmtPrgm0
				Uint16,
				tsa3000c01v1PmtPrgm1
				Uint16,
				tsa3000c01v1PmtPrgm2
				Uint16,
				tsa3000c01v1PmtPrgm3
				Uint16,
				tsa3000c01v1PmtPrgm4
				Uint16,
				tsa3000c01v1PmtPrgm5
				Uint16,
				tsa3000c01v1PmtPrgm6
				Uint16,
				tsa3000c01v1PmtPrgm7
				Uint16,
				tsa3000c01v1PmtPrgm8
				Uint16,
				tsa3000c01v1PmtPrgm9
				Uint16,
				tsa3000c01v1PmtPrgm10
				Uint16,
				tsa3000c01v1PmtPrgm11
				Uint16,
				tsa3000c01v1PmtPrgm12
				Uint16,
				tsa3000c01v1PmtPrgm13
				Uint16,
				tsa3000c01v1PmtPrgm14
				Uint16,
				tsa3000c01v1PmtPrgm15
				Uint16,
				tsa3000c01v1Str1AipDAdd3
				Uint8,
				tsa3000c01v1Str1AipDAdd2
				Uint8,
				tsa3000c01v1Str1AipDAdd1
				Uint8,
				tsa3000c01v1Str1AipDAdd0
				Uint8,
				tsa3000c01v1Str1APortMsb
				Uint8,
				tsa3000c01v1Str1APortLsb
				Uint8,
				tsa3000c01v1Str1IgmAAdd3
				Uint8,
				tsa3000c01v1Str1IgmAAdd2
				Uint8,
				tsa3000c01v1Str1IgmAAdd1
				Uint8,
				tsa3000c01v1Str1IgmAAdd0
				Uint8,
				tsa3000c01v1Str2AipDAdd3
				Uint8,
				tsa3000c01v1Str2AipDAdd2
				Uint8,
				tsa3000c01v1Str2AipDAdd1
				Uint8,
				tsa3000c01v1Str2AipDAdd0
				Uint8,
				tsa3000c01v1Str2APortMsb
				Uint8,
				tsa3000c01v1Str2APortLsb
				Uint8,
				tsa3000c01v1Str2IgmAAdd3
				Uint8,
				tsa3000c01v1Str2IgmAAdd2
				Uint8,
				tsa3000c01v1Str2IgmAAdd1
				Uint8,
				tsa3000c01v1Str2IgmAAdd0
				Uint8,
				tsa3000c01v1PidPacket0
				Uint13,
				tsa3000c01v1PidPacket1
				Uint13,
				tsa3000c01v1PidPacket2
				Uint13,
				tsa3000c01v1PidPacket3
				Uint13,
				tsa3000c01v1PidPacket4
				Uint13,
				tsa3000c01v1PidPacket5
				Uint13,
				tsa3000c01v1PidPacket6
				Uint13,
				tsa3000c01v1PidPacket7
				Uint13,
				tsa3000c01v1PidPacket8
				Uint13,
				tsa3000c01v1PidPacket9
				Uint13,
				tsa3000c01v1PidPacket10
				Uint13,
				tsa3000c01v1PidPacket11
				Uint13,
				tsa3000c01v1PidPacket12
				Uint13,
				tsa3000c01v1PidPacket13
				Uint13,
				tsa3000c01v1PidPacket14
				Uint13,
				tsa3000c01v1PidPacket15
				Uint13,
				tsa3000c01v1PatStat
				TableAnalStat,
				tsa3000c01v1CatStat
				TableAnalStat,
				tsa3000c01v1PmtPrgmStat0
				TableAnalStat,
				tsa3000c01v1PmtPrgmStat1
				TableAnalStat,
				tsa3000c01v1PmtPrgmStat2
				TableAnalStat,
				tsa3000c01v1PmtPrgmStat3
				TableAnalStat,
				tsa3000c01v1PmtPrgmStat4
				TableAnalStat,
				tsa3000c01v1PmtPrgmStat5
				TableAnalStat,
				tsa3000c01v1PmtPrgmStat6
				TableAnalStat,
				tsa3000c01v1PmtPrgmStat7
				TableAnalStat,
				tsa3000c01v1PmtPrgmStat8
				TableAnalStat,
				tsa3000c01v1PmtPrgmStat9
				TableAnalStat,
				tsa3000c01v1PmtPrgmStat10
				TableAnalStat,
				tsa3000c01v1PmtPrgmStat11
				TableAnalStat,
				tsa3000c01v1PmtPrgmStat12
				TableAnalStat,
				tsa3000c01v1PmtPrgmStat13
				TableAnalStat,
				tsa3000c01v1PmtPrgmStat14
				TableAnalStat,
				tsa3000c01v1PmtPrgmStat15
				TableAnalStat,
				tsa3000c01v1BitrateUtil
				BitrateRead,
				tsa3000c01v1OutFail
				BitFail,
				tsa3000c01v1AsiIn1Fail
				BitFail,
				tsa3000c01v1AsiIn1FailTrapEnable
				AlarmEnable,
				tsa3000c01v1ExAsiIn1Fail
				BitFail,
				tsa3000c01v1ExAsiIn1FailTrapEnable
				AlarmEnable,
				tsa3000c01v1AsiIn2Fail
				BitFail,
				tsa3000c01v1AsiIn2FailTrapEnable
				AlarmEnable,
				tsa3000c01v1ExAsiIn2Fail
				BitFail,
				tsa3000c01v1ExAsiIn2FailTrapEnable
				AlarmEnable,
				tsa3000c01v1IpIn1Fail
				BitFail,
				tsa3000c01v1IpIn1FailTrapEnable
				AlarmEnable,
				tsa3000c01v1ExIpIn1Fail
				BitFail,
				tsa3000c01v1ExIpIn1FailTrapEnable
				AlarmEnable,
				tsa3000c01v1IpIn2Fail
				BitFail,
				tsa3000c01v1IpIn2FailTrapEnable
				AlarmEnable,
				tsa3000c01v1ExIpIn2Fail
				BitFail,
				tsa3000c01v1ExIpIn2FailTrapEnable
				AlarmEnable,
				tsa3000c01v1DestAvailable1
				Bit0No1Yes,
				tsa3000c01v1BlindModStat1
				BlindModeStat,
				tsa3000c01v1BlindModStat2
				BlindModeStat,
				tsa3000c01v1AsiIn1Delay
				DelayX131Ms,
				tsa3000c01v1AsiIn2Delay
				DelayX131Ms,
				tsa3000c01v1IpIn1Delay
				DelayX131Ms,
				tsa3000c01v1IpIn2Delay
				DelayX131Ms,
				tsa3000c01v1IpRxAddress3
				Uint8,
				tsa3000c01v1IpRxAddress2
				Uint8,
				tsa3000c01v1IpRxAddress1
				Uint8,
				tsa3000c01v1IpRxAddress0
				Uint8,
				tsa3000c01v1IpRxPort
				Uint16,
				tsa3000c01v1LParam
				Uint5,
				tsa3000c01v1FecMode
				FecMode,
				tsa3000c01v1PacketSize
				Bit02041188,
				tsa3000c01v1DParam
				Uint5,
				tsa3000c01v1TsPckInIpPck
				Uint3,
				tsa3000c01v1PacketRate
				PacketRate,
				tsa3000c01v1TimeSinceReset
				TimeS4,
				tsa3000c01v1LostIpPck
				Uint16,
				tsa3000c01v1RecoveredIpPck
				Uint16,
				tsa3000c01v1OutOrdIpPck
				Uint16,
				tsa3000c01v1FecRate
				PacketRate,
				tsa3000c01v1Link
				IpaEtherStat,
				tsa3000c01v1LinkTrapEnable
				AlarmEnable,
				tsa3000c01v1BufferStatus
				Rate1,
				tsa3000c01v1PingStatus1
				IpaPingStat,
				tsa3000c01v1SerialNo
				SerialNo,
				tsa3000c01v1SpeedForce
				Bit0Ann1For,
				tsa3000c01v1BadCrcPck
				Uint16
			 }

		-- 1.3.6.1.4.1.10106.3.101291.1.1.1
		tsa3000c01v1Index OBJECT-TYPE
			SYNTAX ModuleIndex
			MAX-ACCESS read-only
			STATUS current
			DESCRIPTION
				"Index of TSA3000C01V1 Table"
		::= { tsa3000c01v1Entry 1 }

		-- 1.3.6.1.4.1.10106.3.101291.1.1.3
		tsa3000c01v1Mode OBJECT-TYPE
			SYNTAX ChgOverMode2
			MAX-ACCESS read-write
			STATUS current
			DESCRIPTION
				"Allows selecting the switching mode"
		::= { tsa3000c01v1Entry 3 }

		-- 1.3.6.1.4.1.10106.3.101291.1.1.4
		tsa3000c01v1ModeTrapEnable OBJECT-TYPE
			SYNTAX AlarmEnable
			MAX-ACCESS read-write
			STATUS current
			DESCRIPTION
				"Allows selecting the switching mode Trap Enable"
		::= { tsa3000c01v1Entry 4 }

		-- 1.3.6.1.4.1.10106.3.101291.1.1.5
		tsa3000c01v1NullPckRtp OBJECT-TYPE
			SYNTAX Bit0No1Yes
			MAX-ACCESS read-write
			STATUS current
			DESCRIPTION
				"Selects if null packets are inserted if there are unrecovered packets when using RTP protocol"
		::= { tsa3000c01v1Entry 5 }

		-- 1.3.6.1.4.1.10106.3.101291.1.1.7
		tsa3000c01v1NarrowPllBw OBJECT-TYPE
			SYNTAX Bit0No1Yes
			MAX-ACCESS read-write
			STATUS current
			DESCRIPTION
				"Allows selecting a narrow PLL bandwidth in the clock packet PLL to achieve a very stable bitrate"
		::= { tsa3000c01v1Entry 7 }

		-- 1.3.6.1.4.1.10106.3.101291.1.1.9
		tsa3000c01v1Buzzer OBJECT-TYPE
			SYNTAX BitMask
			MAX-ACCESS read-write
			STATUS current
			DESCRIPTION
				"Allows buzzer operation"
		::= { tsa3000c01v1Entry 9 }

		-- 1.3.6.1.4.1.10106.3.101291.1.1.11
		tsa3000c01v1GpioMode OBJECT-TYPE
			SYNTAX GpioModeB
			MAX-ACCESS read-write
			STATUS current
			DESCRIPTION
				"Selects the GPIO's configurable mode"
		::= { tsa3000c01v1Entry 11 }

		-- 1.3.6.1.4.1.10106.3.101291.1.1.13
		tsa3000c01v1InputStChange OBJECT-TYPE
			SYNTAX Bit0No1Yes
			MAX-ACCESS read-write
			STATUS current
			DESCRIPTION
				"Signals a change in fail status"
		::= { tsa3000c01v1Entry 13 }

		-- 1.3.6.1.4.1.10106.3.101291.1.1.15
		tsa3000c01v1InputChange OBJECT-TYPE
			SYNTAX Bit0No1Yes
			MAX-ACCESS read-write
			STATUS current
			DESCRIPTION
				"Signals a change in selected input"
		::= { tsa3000c01v1Entry 15 }

		-- 1.3.6.1.4.1.10106.3.101291.1.1.17
		tsa3000c01v1EnaAsi1 OBJECT-TYPE
			SYNTAX BitMask
			MAX-ACCESS read-write
			STATUS current
			DESCRIPTION
				"Allows disabling ASI input 1 when it is not used"
		::= { tsa3000c01v1Entry 17 }

		-- 1.3.6.1.4.1.10106.3.101291.1.1.19
		tsa3000c01v1EnaAsi2 OBJECT-TYPE
			SYNTAX BitMask
			MAX-ACCESS read-write
			STATUS current
			DESCRIPTION
				"Allows disabling ASI input 2 when it is not used"
		::= { tsa3000c01v1Entry 19 }

		-- 1.3.6.1.4.1.10106.3.101291.1.1.21
		tsa3000c01v1EnaIp1 OBJECT-TYPE
			SYNTAX BitMask
			MAX-ACCESS read-write
			STATUS current
			DESCRIPTION
				"Allows disabling IP input 1 when it is not used"
		::= { tsa3000c01v1Entry 21 }

		-- 1.3.6.1.4.1.10106.3.101291.1.1.23
		tsa3000c01v1EnaIp2 OBJECT-TYPE
			SYNTAX BitMask
			MAX-ACCESS read-write
			STATUS current
			DESCRIPTION
				"Allows disabling IP input 2 when it is not used"
		::= { tsa3000c01v1Entry 23 }

		-- 1.3.6.1.4.1.10106.3.101291.1.1.25
		tsa3000c01v1SelectedInput OBJECT-TYPE
			SYNTAX GatewayInput3
			MAX-ACCESS read-write
			STATUS current
			DESCRIPTION
				"Selected input"
		::= { tsa3000c01v1Entry 25 }

		-- 1.3.6.1.4.1.10106.3.101291.1.1.26
		tsa3000c01v1SelectedInputTrapEnable OBJECT-TYPE
			SYNTAX AlarmEnable
			MAX-ACCESS read-write
			STATUS current
			DESCRIPTION
				"Selected input Trap Enable"
		::= { tsa3000c01v1Entry 26 }

		-- 1.3.6.1.4.1.10106.3.101291.1.1.27
		tsa3000c01v1PingEnable1 OBJECT-TYPE
			SYNTAX Bit0No1Yes
			MAX-ACCESS read-write
			STATUS current
			DESCRIPTION
				"Allows making a periodic ping to the unicast address"
		::= { tsa3000c01v1Entry 27 }

		-- 1.3.6.1.4.1.10106.3.101291.1.1.29
		tsa3000c01v1IpLinkFailEn OBJECT-TYPE
			SYNTAX Bit0No1Yes
			MAX-ACCESS read-write
			STATUS current
			DESCRIPTION
				"IP link lose signals fail in F_OUT GPO"
		::= { tsa3000c01v1Entry 29 }

		-- 1.3.6.1.4.1.10106.3.101291.1.1.31
		tsa3000c01v1IpDestFailEn OBJECT-TYPE
			SYNTAX Bit0No1Yes
			MAX-ACCESS read-write
			STATUS current
			DESCRIPTION
				"IP destination absence signals fail in F_OUT GPO"
		::= { tsa3000c01v1Entry 31 }

		-- 1.3.6.1.4.1.10106.3.101291.1.1.33
		tsa3000c01v1MaxTimeOut OBJECT-TYPE
			SYNTAX TimeX1Ms1
			MAX-ACCESS read-write
			STATUS current
			DESCRIPTION
				"Maximum time out for IP channels without receiving any packet.  It limits the low frequency jitter capacity."
		::= { tsa3000c01v1Entry 33 }

		-- 1.3.6.1.4.1.10106.3.101291.1.1.35
		tsa3000c01v1StatReset OBJECT-TYPE
			SYNTAX Bit0No1Yes
			MAX-ACCESS read-write
			STATUS current
			DESCRIPTION
				"Allows reseting the statistics measurements"
		::= { tsa3000c01v1Entry 35 }

		-- 1.3.6.1.4.1.10106.3.101291.1.1.37
		tsa3000c01v1StatSel OBJECT-TYPE
			SYNTAX Bit0Ipm1Ipr
			MAX-ACCESS read-write
			STATUS current
			DESCRIPTION
				"Allows selecting the channel to be displayed"
		::= { tsa3000c01v1Entry 37 }

		-- 1.3.6.1.4.1.10106.3.101291.1.1.39
		tsa3000c01v1StatMode OBJECT-TYPE
			SYNTAX Bit01s1Total
			MAX-ACCESS read-write
			STATUS current
			DESCRIPTION
				"Allows selecting the statistics mode"
		::= { tsa3000c01v1Entry 39 }

		-- 1.3.6.1.4.1.10106.3.101291.1.1.41
		tsa3000c01v1IgmpVersion OBJECT-TYPE
			SYNTAX Bit0V21V3
			MAX-ACCESS read-write
			STATUS current
			DESCRIPTION
				"Allows selecting the IGMP version"
		::= { tsa3000c01v1Entry 41 }

		-- 1.3.6.1.4.1.10106.3.101291.1.1.43
		tsa3000c01v1EthMode OBJECT-TYPE
			SYNTAX EthMode
			MAX-ACCESS read-write
			STATUS current
			DESCRIPTION
				"Allows selecting the Ethernet operating mode"
		::= { tsa3000c01v1Entry 43 }

		-- 1.3.6.1.4.1.10106.3.101291.1.1.45
		tsa3000c01v1PckDelAsiIn1 OBJECT-TYPE
			SYNTAX DelayPacket1
			MAX-ACCESS read-write
			STATUS current
			DESCRIPTION
				"Buffer size in packets for the ASI input 1"
		::= { tsa3000c01v1Entry 45 }

		-- 1.3.6.1.4.1.10106.3.101291.1.1.47
		tsa3000c01v1PckDelAsiIn2 OBJECT-TYPE
			SYNTAX DelayPacket1
			MAX-ACCESS read-write
			STATUS current
			DESCRIPTION
				"Buffer size in packets for the ASI input 2"
		::= { tsa3000c01v1Entry 47 }

		-- 1.3.6.1.4.1.10106.3.101291.1.1.49
		tsa3000c01v1PckDelIpIn1 OBJECT-TYPE
			SYNTAX DelayPacket1
			MAX-ACCESS read-write
			STATUS current
			DESCRIPTION
				"Buffer size in packets for the IP input 1"
		::= { tsa3000c01v1Entry 49 }

		-- 1.3.6.1.4.1.10106.3.101291.1.1.51
		tsa3000c01v1PckDelIpIn2 OBJECT-TYPE
			SYNTAX DelayPacket1
			MAX-ACCESS read-write
			STATUS current
			DESCRIPTION
				"Buffer size in packets for the IP input 2"
		::= { tsa3000c01v1Entry 51 }

		-- 1.3.6.1.4.1.10106.3.101291.1.1.53
		tsa3000c01v1AsiIn1Prior0 OBJECT-TYPE
			SYNTAX Uint2
			MAX-ACCESS read-write
			STATUS current
			DESCRIPTION
				"Allows selecting the ASI IN 1 input priority"
		::= { tsa3000c01v1Entry 53 }

		-- 1.3.6.1.4.1.10106.3.101291.1.1.55
		tsa3000c01v1AsiIn2Prior0 OBJECT-TYPE
			SYNTAX Uint2
			MAX-ACCESS read-write
			STATUS current
			DESCRIPTION
				"Allows selecting the ASI IN 2 input priority"
		::= { tsa3000c01v1Entry 55 }

		-- 1.3.6.1.4.1.10106.3.101291.1.1.57
		tsa3000c01v1IpIn1Prior0 OBJECT-TYPE
			SYNTAX Uint2
			MAX-ACCESS read-write
			STATUS current
			DESCRIPTION
				"Allows selecting the IP IN 1 input priority"
		::= { tsa3000c01v1Entry 57 }

		-- 1.3.6.1.4.1.10106.3.101291.1.1.59
		tsa3000c01v1IpIn2Prior0 OBJECT-TYPE
			SYNTAX Uint2
			MAX-ACCESS read-write
			STATUS current
			DESCRIPTION
				"Allows selecting the IP IN 2 input priority"
		::= { tsa3000c01v1Entry 59 }

		-- 1.3.6.1.4.1.10106.3.101291.1.1.61
		tsa3000c01v1BitrateEn OBJECT-TYPE
			SYNTAX Bit0No1Yes
			MAX-ACCESS read-write
			STATUS current
			DESCRIPTION
				"Output bitrate control enable.  It stuffs the TS with null packets"
		::= { tsa3000c01v1Entry 61 }

		-- 1.3.6.1.4.1.10106.3.101291.1.1.63
		tsa3000c01v1Bitrate OBJECT-TYPE
			SYNTAX BitrateControl
			MAX-ACCESS read-write
			STATUS current
			DESCRIPTION
				"Target value for the output bitrate"
		::= { tsa3000c01v1Entry 63 }

		-- 1.3.6.1.4.1.10106.3.101291.1.1.65
		tsa3000c01v1FilterEn OBJECT-TYPE
			SYNTAX Bit0Dis1Ena
			MAX-ACCESS read-write
			STATUS current
			DESCRIPTION
				"Enables transport stream filtering"
		::= { tsa3000c01v1Entry 65 }

		-- 1.3.6.1.4.1.10106.3.101291.1.1.67
		tsa3000c01v1PatPidsEn OBJECT-TYPE
			SYNTAX Bit0Dis1Ena
			MAX-ACCESS read-write
			STATUS current
			DESCRIPTION
				"Enables pass of PAT PIDs"
		::= { tsa3000c01v1Entry 67 }

		-- 1.3.6.1.4.1.10106.3.101291.1.1.69
		tsa3000c01v1CatPidsEn OBJECT-TYPE
			SYNTAX Bit0Dis1Ena
			MAX-ACCESS read-write
			STATUS current
			DESCRIPTION
				"Enables pass of CAT PIDs"
		::= { tsa3000c01v1Entry 69 }

		-- 1.3.6.1.4.1.10106.3.101291.1.1.71
		tsa3000c01v1PmtPrgmEn OBJECT-TYPE
			SYNTAX Bit0Dis1Ena
			MAX-ACCESS read-write
			STATUS current
			DESCRIPTION
				"Enables filtering of PMTs programs"
		::= { tsa3000c01v1Entry 71 }

		-- 1.3.6.1.4.1.10106.3.101291.1.1.73
		tsa3000c01v1RsrvedPidsEn OBJECT-TYPE
			SYNTAX Bit0Dis1Ena
			MAX-ACCESS read-write
			STATUS current
			DESCRIPTION
				"Enables filtering of reserved PIDs"
		::= { tsa3000c01v1Entry 73 }

		-- 1.3.6.1.4.1.10106.3.101291.1.1.75
		tsa3000c01v1NullPckEn OBJECT-TYPE
			SYNTAX Bit0Dis1Ena
			MAX-ACCESS read-write
			STATUS current
			DESCRIPTION
				"Enables pass of null packets"
		::= { tsa3000c01v1Entry 75 }

		-- 1.3.6.1.4.1.10106.3.101291.1.1.77
		tsa3000c01v1InvertFilter OBJECT-TYPE
			SYNTAX Bit0Pass1Rem
			MAX-ACCESS read-write
			STATUS current
			DESCRIPTION
				"Allows selected programs to be removed or to pass"
		::= { tsa3000c01v1Entry 77 }

		-- 1.3.6.1.4.1.10106.3.101291.1.1.79
		tsa3000c01v1PmtPrgmEn0 OBJECT-TYPE
			SYNTAX Bit0No1Yes
			MAX-ACCESS read-write
			STATUS current
			DESCRIPTION
				"Enables program filter 1"
		::= { tsa3000c01v1Entry 79 }

		-- 1.3.6.1.4.1.10106.3.101291.1.1.81
		tsa3000c01v1PmtPrgmEn1 OBJECT-TYPE
			SYNTAX Bit0No1Yes
			MAX-ACCESS read-write
			STATUS current
			DESCRIPTION
				"Enables program filter 2"
		::= { tsa3000c01v1Entry 81 }

		-- 1.3.6.1.4.1.10106.3.101291.1.1.83
		tsa3000c01v1PmtPrgmEn2 OBJECT-TYPE
			SYNTAX Bit0No1Yes
			MAX-ACCESS read-write
			STATUS current
			DESCRIPTION
				"Enables program filter 3"
		::= { tsa3000c01v1Entry 83 }

		-- 1.3.6.1.4.1.10106.3.101291.1.1.85
		tsa3000c01v1PmtPrgmEn3 OBJECT-TYPE
			SYNTAX Bit0No1Yes
			MAX-ACCESS read-write
			STATUS current
			DESCRIPTION
				"Enables program filter 4"
		::= { tsa3000c01v1Entry 85 }

		-- 1.3.6.1.4.1.10106.3.101291.1.1.87
		tsa3000c01v1PmtPrgmEn4 OBJECT-TYPE
			SYNTAX Bit0No1Yes
			MAX-ACCESS read-write
			STATUS current
			DESCRIPTION
				"Enables program filter 5"
		::= { tsa3000c01v1Entry 87 }

		-- 1.3.6.1.4.1.10106.3.101291.1.1.89
		tsa3000c01v1PmtPrgmEn5 OBJECT-TYPE
			SYNTAX Bit0No1Yes
			MAX-ACCESS read-write
			STATUS current
			DESCRIPTION
				"Enables program filter 6"
		::= { tsa3000c01v1Entry 89 }

		-- 1.3.6.1.4.1.10106.3.101291.1.1.91
		tsa3000c01v1PmtPrgmEn6 OBJECT-TYPE
			SYNTAX Bit0No1Yes
			MAX-ACCESS read-write
			STATUS current
			DESCRIPTION
				"Enables program filter 7"
		::= { tsa3000c01v1Entry 91 }

		-- 1.3.6.1.4.1.10106.3.101291.1.1.93
		tsa3000c01v1PmtPrgmEn7 OBJECT-TYPE
			SYNTAX Bit0No1Yes
			MAX-ACCESS read-write
			STATUS current
			DESCRIPTION
				"Enables program filter 8"
		::= { tsa3000c01v1Entry 93 }

		-- 1.3.6.1.4.1.10106.3.101291.1.1.95
		tsa3000c01v1PmtPrgmEn8 OBJECT-TYPE
			SYNTAX Bit0No1Yes
			MAX-ACCESS read-write
			STATUS current
			DESCRIPTION
				"Enables program filter 9"
		::= { tsa3000c01v1Entry 95 }

		-- 1.3.6.1.4.1.10106.3.101291.1.1.97
		tsa3000c01v1PmtPrgmEn9 OBJECT-TYPE
			SYNTAX Bit0No1Yes
			MAX-ACCESS read-write
			STATUS current
			DESCRIPTION
				"Enables program filter 10"
		::= { tsa3000c01v1Entry 97 }

		-- 1.3.6.1.4.1.10106.3.101291.1.1.99
		tsa3000c01v1PmtPrgmEn10 OBJECT-TYPE
			SYNTAX Bit0No1Yes
			MAX-ACCESS read-write
			STATUS current
			DESCRIPTION
				"Enables program filter 11"
		::= { tsa3000c01v1Entry 99 }

		-- 1.3.6.1.4.1.10106.3.101291.1.1.101
		tsa3000c01v1PmtPrgmEn11 OBJECT-TYPE
			SYNTAX Bit0No1Yes
			MAX-ACCESS read-write
			STATUS current
			DESCRIPTION
				"Enables program filter 12"
		::= { tsa3000c01v1Entry 101 }

		-- 1.3.6.1.4.1.10106.3.101291.1.1.103
		tsa3000c01v1PmtPrgmEn12 OBJECT-TYPE
			SYNTAX Bit0No1Yes
			MAX-ACCESS read-write
			STATUS current
			DESCRIPTION
				"Enables program filter 13"
		::= { tsa3000c01v1Entry 103 }

		-- 1.3.6.1.4.1.10106.3.101291.1.1.105
		tsa3000c01v1PmtPrgmEn13 OBJECT-TYPE
			SYNTAX Bit0No1Yes
			MAX-ACCESS read-write
			STATUS current
			DESCRIPTION
				"Enables program filter 14"
		::= { tsa3000c01v1Entry 105 }

		-- 1.3.6.1.4.1.10106.3.101291.1.1.107
		tsa3000c01v1PmtPrgmEn14 OBJECT-TYPE
			SYNTAX Bit0No1Yes
			MAX-ACCESS read-write
			STATUS current
			DESCRIPTION
				"Enables program filter 15"
		::= { tsa3000c01v1Entry 107 }

		-- 1.3.6.1.4.1.10106.3.101291.1.1.109
		tsa3000c01v1PmtPrgmEn15 OBJECT-TYPE
			SYNTAX Bit0No1Yes
			MAX-ACCESS read-write
			STATUS current
			DESCRIPTION
				"Enables program filter 16"
		::= { tsa3000c01v1Entry 109 }

		-- 1.3.6.1.4.1.10106.3.101291.1.1.111
		tsa3000c01v1PidPacketEn0 OBJECT-TYPE
			SYNTAX Bit0No1Yes
			MAX-ACCESS read-write
			STATUS current
			DESCRIPTION
				"Enables PID filter 1"
		::= { tsa3000c01v1Entry 111 }

		-- 1.3.6.1.4.1.10106.3.101291.1.1.113
		tsa3000c01v1PidPacketEn1 OBJECT-TYPE
			SYNTAX Bit0No1Yes
			MAX-ACCESS read-write
			STATUS current
			DESCRIPTION
				"Enables PID filter 2"
		::= { tsa3000c01v1Entry 113 }

		-- 1.3.6.1.4.1.10106.3.101291.1.1.115
		tsa3000c01v1PidPacketEn2 OBJECT-TYPE
			SYNTAX Bit0No1Yes
			MAX-ACCESS read-write
			STATUS current
			DESCRIPTION
				"Enables PID filter 3"
		::= { tsa3000c01v1Entry 115 }

		-- 1.3.6.1.4.1.10106.3.101291.1.1.117
		tsa3000c01v1PidPacketEn3 OBJECT-TYPE
			SYNTAX Bit0No1Yes
			MAX-ACCESS read-write
			STATUS current
			DESCRIPTION
				"Enables PID filter 4"
		::= { tsa3000c01v1Entry 117 }

		-- 1.3.6.1.4.1.10106.3.101291.1.1.119
		tsa3000c01v1PidPacketEn4 OBJECT-TYPE
			SYNTAX Bit0No1Yes
			MAX-ACCESS read-write
			STATUS current
			DESCRIPTION
				"Enables PID filter 5"
		::= { tsa3000c01v1Entry 119 }

		-- 1.3.6.1.4.1.10106.3.101291.1.1.121
		tsa3000c01v1PidPacketEn5 OBJECT-TYPE
			SYNTAX Bit0No1Yes
			MAX-ACCESS read-write
			STATUS current
			DESCRIPTION
				"Enables PID filter 6"
		::= { tsa3000c01v1Entry 121 }

		-- 1.3.6.1.4.1.10106.3.101291.1.1.123
		tsa3000c01v1PidPacketEn6 OBJECT-TYPE
			SYNTAX Bit0No1Yes
			MAX-ACCESS read-write
			STATUS current
			DESCRIPTION
				"Enables PID filter 7"
		::= { tsa3000c01v1Entry 123 }

		-- 1.3.6.1.4.1.10106.3.101291.1.1.125
		tsa3000c01v1PidPacketEn7 OBJECT-TYPE
			SYNTAX Bit0No1Yes
			MAX-ACCESS read-write
			STATUS current
			DESCRIPTION
				"Enables PID filter 8"
		::= { tsa3000c01v1Entry 125 }

		-- 1.3.6.1.4.1.10106.3.101291.1.1.127
		tsa3000c01v1PidPacketEn8 OBJECT-TYPE
			SYNTAX Bit0No1Yes
			MAX-ACCESS read-write
			STATUS current
			DESCRIPTION
				"Enables PID filter 9"
		::= { tsa3000c01v1Entry 127 }

		-- 1.3.6.1.4.1.10106.3.101291.1.1.129
		tsa3000c01v1PidPacketEn9 OBJECT-TYPE
			SYNTAX Bit0No1Yes
			MAX-ACCESS read-write
			STATUS current
			DESCRIPTION
				"Enables PID filter 10"
		::= { tsa3000c01v1Entry 129 }

		-- 1.3.6.1.4.1.10106.3.101291.1.1.131
		tsa3000c01v1PidPacketEn10 OBJECT-TYPE
			SYNTAX Bit0No1Yes
			MAX-ACCESS read-write
			STATUS current
			DESCRIPTION
				"Enables PID filter 11"
		::= { tsa3000c01v1Entry 131 }

		-- 1.3.6.1.4.1.10106.3.101291.1.1.133
		tsa3000c01v1PidPacketEn11 OBJECT-TYPE
			SYNTAX Bit0No1Yes
			MAX-ACCESS read-write
			STATUS current
			DESCRIPTION
				"Enables PID filter 12"
		::= { tsa3000c01v1Entry 133 }

		-- 1.3.6.1.4.1.10106.3.101291.1.1.135
		tsa3000c01v1PidPacketEn12 OBJECT-TYPE
			SYNTAX Bit0No1Yes
			MAX-ACCESS read-write
			STATUS current
			DESCRIPTION
				"Enables PID filter 13"
		::= { tsa3000c01v1Entry 135 }

		-- 1.3.6.1.4.1.10106.3.101291.1.1.137
		tsa3000c01v1PidPacketEn13 OBJECT-TYPE
			SYNTAX Bit0No1Yes
			MAX-ACCESS read-write
			STATUS current
			DESCRIPTION
				"Enables PID filter 14"
		::= { tsa3000c01v1Entry 137 }

		-- 1.3.6.1.4.1.10106.3.101291.1.1.139
		tsa3000c01v1PidPacketEn14 OBJECT-TYPE
			SYNTAX Bit0No1Yes
			MAX-ACCESS read-write
			STATUS current
			DESCRIPTION
				"Enables PID filter 15"
		::= { tsa3000c01v1Entry 139 }

		-- 1.3.6.1.4.1.10106.3.101291.1.1.141
		tsa3000c01v1PidPacketEn15 OBJECT-TYPE
			SYNTAX Bit0No1Yes
			MAX-ACCESS read-write
			STATUS current
			DESCRIPTION
				"Enables PID filter 16"
		::= { tsa3000c01v1Entry 141 }

		-- 1.3.6.1.4.1.10106.3.101291.1.1.143
		tsa3000c01v1ActivePreset OBJECT-TYPE
			SYNTAX Preset16Active
			MAX-ACCESS read-only
			STATUS current
			DESCRIPTION
				"Shows the active preset"
		::= { tsa3000c01v1Entry 143 }

		-- 1.3.6.1.4.1.10106.3.101291.1.1.145
		tsa3000c01v1LoadPreset OBJECT-TYPE
			SYNTAX Preset16Load
			MAX-ACCESS read-write
			STATUS current
			DESCRIPTION
				"Allows loading a preset"
		::= { tsa3000c01v1Entry 145 }

		-- 1.3.6.1.4.1.10106.3.101291.1.1.147
		tsa3000c01v1SavePreset OBJECT-TYPE
			SYNTAX Preset16Save
			MAX-ACCESS read-write
			STATUS current
			DESCRIPTION
				"Allows saving a preset"
		::= { tsa3000c01v1Entry 147 }

		-- 1.3.6.1.4.1.10106.3.101291.1.1.149
		tsa3000c01v1Str1UipDAdd3 OBJECT-TYPE
			SYNTAX Uint8
			MAX-ACCESS read-write
			STATUS current
			DESCRIPTION
				"Unicast IP address (3)"
		::= { tsa3000c01v1Entry 149 }

		-- 1.3.6.1.4.1.10106.3.101291.1.1.151
		tsa3000c01v1Str1UipDAdd2 OBJECT-TYPE
			SYNTAX Uint8
			MAX-ACCESS read-write
			STATUS current
			DESCRIPTION
				"Unicast IP address (2)"
		::= { tsa3000c01v1Entry 151 }

		-- 1.3.6.1.4.1.10106.3.101291.1.1.153
		tsa3000c01v1Str1UipDAdd1 OBJECT-TYPE
			SYNTAX Uint8
			MAX-ACCESS read-write
			STATUS current
			DESCRIPTION
				"Unicast IP address (1)"
		::= { tsa3000c01v1Entry 153 }

		-- 1.3.6.1.4.1.10106.3.101291.1.1.155
		tsa3000c01v1Str1UipDAdd0 OBJECT-TYPE
			SYNTAX Uint8
			MAX-ACCESS read-write
			STATUS current
			DESCRIPTION
				"Unicast IP address (0)"
		::= { tsa3000c01v1Entry 155 }

		-- 1.3.6.1.4.1.10106.3.101291.1.1.157
		tsa3000c01v1Str1MipDAdd3 OBJECT-TYPE
			SYNTAX Uint8
			MAX-ACCESS read-write
			STATUS current
			DESCRIPTION
				"Multicast IP address (3)"
		::= { tsa3000c01v1Entry 157 }

		-- 1.3.6.1.4.1.10106.3.101291.1.1.159
		tsa3000c01v1Str1MipDAdd2 OBJECT-TYPE
			SYNTAX Uint8
			MAX-ACCESS read-write
			STATUS current
			DESCRIPTION
				"Multicast IP address (2)"
		::= { tsa3000c01v1Entry 159 }

		-- 1.3.6.1.4.1.10106.3.101291.1.1.161
		tsa3000c01v1Str1MipDAdd1 OBJECT-TYPE
			SYNTAX Uint8
			MAX-ACCESS read-write
			STATUS current
			DESCRIPTION
				"Multicast IP address (1)"
		::= { tsa3000c01v1Entry 161 }

		-- 1.3.6.1.4.1.10106.3.101291.1.1.163
		tsa3000c01v1Str1MipDAdd0 OBJECT-TYPE
			SYNTAX Uint8
			MAX-ACCESS read-write
			STATUS current
			DESCRIPTION
				"Multicast IP address (0)"
		::= { tsa3000c01v1Entry 163 }

		-- 1.3.6.1.4.1.10106.3.101291.1.1.165
		tsa3000c01v1Str1DPort OBJECT-TYPE
			SYNTAX Uint16
			MAX-ACCESS read-write
			STATUS current
			DESCRIPTION
				"Destination port"
		::= { tsa3000c01v1Entry 165 }

		-- 1.3.6.1.4.1.10106.3.101291.1.1.167
		tsa3000c01v1Str1FecEna OBJECT-TYPE
			SYNTAX Bit0No1Yes
			MAX-ACCESS read-write
			STATUS current
			DESCRIPTION
				"Enable FEC"
		::= { tsa3000c01v1Entry 167 }

		-- 1.3.6.1.4.1.10106.3.101291.1.1.169
		tsa3000c01v1Str1MulticEna OBJECT-TYPE
			SYNTAX IpaTxMode
			MAX-ACCESS read-write
			STATUS current
			DESCRIPTION
				"RX mode"
		::= { tsa3000c01v1Entry 169 }

		-- 1.3.6.1.4.1.10106.3.101291.1.1.171
		tsa3000c01v1VlanRx1Enable OBJECT-TYPE
			SYNTAX Bit0No1Yes
			MAX-ACCESS read-write
			STATUS current
			DESCRIPTION
				"VLAN Enable"
		::= { tsa3000c01v1Entry 171 }

		-- 1.3.6.1.4.1.10106.3.101291.1.1.173
		tsa3000c01v1VlanRx1Id OBJECT-TYPE
			SYNTAX Uint12
			MAX-ACCESS read-write
			STATUS current
			DESCRIPTION
				"VLAN ID"
		::= { tsa3000c01v1Entry 173 }

		-- 1.3.6.1.4.1.10106.3.101291.1.1.175
		tsa3000c01v1Str2UipDAdd3 OBJECT-TYPE
			SYNTAX Uint8
			MAX-ACCESS read-write
			STATUS current
			DESCRIPTION
				"Unicast IP address (3)"
		::= { tsa3000c01v1Entry 175 }

		-- 1.3.6.1.4.1.10106.3.101291.1.1.177
		tsa3000c01v1Str2UipDAdd2 OBJECT-TYPE
			SYNTAX Uint8
			MAX-ACCESS read-write
			STATUS current
			DESCRIPTION
				"Unicast IP address (2)"
		::= { tsa3000c01v1Entry 177 }

		-- 1.3.6.1.4.1.10106.3.101291.1.1.179
		tsa3000c01v1Str2UipDAdd1 OBJECT-TYPE
			SYNTAX Uint8
			MAX-ACCESS read-write
			STATUS current
			DESCRIPTION
				"Unicast IP address (1)"
		::= { tsa3000c01v1Entry 179 }

		-- 1.3.6.1.4.1.10106.3.101291.1.1.181
		tsa3000c01v1Str2UipDAdd0 OBJECT-TYPE
			SYNTAX Uint8
			MAX-ACCESS read-write
			STATUS current
			DESCRIPTION
				"Unicast IP address (0)"
		::= { tsa3000c01v1Entry 181 }

		-- 1.3.6.1.4.1.10106.3.101291.1.1.183
		tsa3000c01v1Str2MipDAdd3 OBJECT-TYPE
			SYNTAX Uint8
			MAX-ACCESS read-write
			STATUS current
			DESCRIPTION
				"Multicast IP address (3)"
		::= { tsa3000c01v1Entry 183 }

		-- 1.3.6.1.4.1.10106.3.101291.1.1.185
		tsa3000c01v1Str2MipDAdd2 OBJECT-TYPE
			SYNTAX Uint8
			MAX-ACCESS read-write
			STATUS current
			DESCRIPTION
				"Multicast IP address (2)"
		::= { tsa3000c01v1Entry 185 }

		-- 1.3.6.1.4.1.10106.3.101291.1.1.187
		tsa3000c01v1Str2MipDAdd1 OBJECT-TYPE
			SYNTAX Uint8
			MAX-ACCESS read-write
			STATUS current
			DESCRIPTION
				"Multicast IP address (1)"
		::= { tsa3000c01v1Entry 187 }

		-- 1.3.6.1.4.1.10106.3.101291.1.1.189
		tsa3000c01v1Str2MipDAdd0 OBJECT-TYPE
			SYNTAX Uint8
			MAX-ACCESS read-write
			STATUS current
			DESCRIPTION
				"Multicast IP address (0)"
		::= { tsa3000c01v1Entry 189 }

		-- 1.3.6.1.4.1.10106.3.101291.1.1.191
		tsa3000c01v1Str2DPort OBJECT-TYPE
			SYNTAX Uint16
			MAX-ACCESS read-write
			STATUS current
			DESCRIPTION
				"Destination port"
		::= { tsa3000c01v1Entry 191 }

		-- 1.3.6.1.4.1.10106.3.101291.1.1.193
		tsa3000c01v1Str2FecEna OBJECT-TYPE
			SYNTAX Bit0No1Yes
			MAX-ACCESS read-write
			STATUS current
			DESCRIPTION
				"Enable FEC"
		::= { tsa3000c01v1Entry 193 }

		-- 1.3.6.1.4.1.10106.3.101291.1.1.195
		tsa3000c01v1Str2MulticEna OBJECT-TYPE
			SYNTAX IpaTxMode
			MAX-ACCESS read-write
			STATUS current
			DESCRIPTION
				"RX mode"
		::= { tsa3000c01v1Entry 195 }

		-- 1.3.6.1.4.1.10106.3.101291.1.1.197
		tsa3000c01v1VlanRx2Enable OBJECT-TYPE
			SYNTAX Bit0No1Yes
			MAX-ACCESS read-write
			STATUS current
			DESCRIPTION
				"VLAN Enable"
		::= { tsa3000c01v1Entry 197 }

		-- 1.3.6.1.4.1.10106.3.101291.1.1.199
		tsa3000c01v1VlanRx2Id OBJECT-TYPE
			SYNTAX Uint12
			MAX-ACCESS read-write
			STATUS current
			DESCRIPTION
				"VLAN ID"
		::= { tsa3000c01v1Entry 199 }

		-- 1.3.6.1.4.1.10106.3.101291.1.1.201
		tsa3000c01v1LocalIpAdd3 OBJECT-TYPE
			SYNTAX Uint8
			MAX-ACCESS read-write
			STATUS current
			DESCRIPTION
				"IP address (3)"
		::= { tsa3000c01v1Entry 201 }

		-- 1.3.6.1.4.1.10106.3.101291.1.1.203
		tsa3000c01v1LocalIpAdd2 OBJECT-TYPE
			SYNTAX Uint8
			MAX-ACCESS read-write
			STATUS current
			DESCRIPTION
				"IP address (2)"
		::= { tsa3000c01v1Entry 203 }

		-- 1.3.6.1.4.1.10106.3.101291.1.1.205
		tsa3000c01v1LocalIpAdd1 OBJECT-TYPE
			SYNTAX Uint8
			MAX-ACCESS read-write
			STATUS current
			DESCRIPTION
				"IP address (1)"
		::= { tsa3000c01v1Entry 205 }

		-- 1.3.6.1.4.1.10106.3.101291.1.1.207
		tsa3000c01v1LocalIpAdd0 OBJECT-TYPE
			SYNTAX Uint8
			MAX-ACCESS read-write
			STATUS current
			DESCRIPTION
				"IP address (0)"
		::= { tsa3000c01v1Entry 207 }

		-- 1.3.6.1.4.1.10106.3.101291.1.1.209
		tsa3000c01v1LocalIpMask3 OBJECT-TYPE
			SYNTAX Uint8
			MAX-ACCESS read-write
			STATUS current
			DESCRIPTION
				"IP mask (3)"
		::= { tsa3000c01v1Entry 209 }

		-- 1.3.6.1.4.1.10106.3.101291.1.1.211
		tsa3000c01v1LocalIpMask2 OBJECT-TYPE
			SYNTAX Uint8
			MAX-ACCESS read-write
			STATUS current
			DESCRIPTION
				"IP mask (2)"
		::= { tsa3000c01v1Entry 211 }

		-- 1.3.6.1.4.1.10106.3.101291.1.1.213
		tsa3000c01v1LocalIpMask1 OBJECT-TYPE
			SYNTAX Uint8
			MAX-ACCESS read-write
			STATUS current
			DESCRIPTION
				"IP mask (1)"
		::= { tsa3000c01v1Entry 213 }

		-- 1.3.6.1.4.1.10106.3.101291.1.1.215
		tsa3000c01v1LocalIpMask0 OBJECT-TYPE
			SYNTAX Uint8
			MAX-ACCESS read-write
			STATUS current
			DESCRIPTION
				"IP mask (0)"
		::= { tsa3000c01v1Entry 215 }

		-- 1.3.6.1.4.1.10106.3.101291.1.1.217
		tsa3000c01v1LocalIpGway3 OBJECT-TYPE
			SYNTAX Uint8
			MAX-ACCESS read-write
			STATUS current
			DESCRIPTION
				"Gateway IP address (3)"
		::= { tsa3000c01v1Entry 217 }

		-- 1.3.6.1.4.1.10106.3.101291.1.1.219
		tsa3000c01v1LocalIpGway2 OBJECT-TYPE
			SYNTAX Uint8
			MAX-ACCESS read-write
			STATUS current
			DESCRIPTION
				"Gateway IP address (2)"
		::= { tsa3000c01v1Entry 219 }

		-- 1.3.6.1.4.1.10106.3.101291.1.1.221
		tsa3000c01v1LocalIpGway1 OBJECT-TYPE
			SYNTAX Uint8
			MAX-ACCESS read-write
			STATUS current
			DESCRIPTION
				"Gateway IP address (1)"
		::= { tsa3000c01v1Entry 221 }

		-- 1.3.6.1.4.1.10106.3.101291.1.1.223
		tsa3000c01v1LocalIpGway0 OBJECT-TYPE
			SYNTAX Uint8
			MAX-ACCESS read-write
			STATUS current
			DESCRIPTION
				"Gateway IP address (0)"
		::= { tsa3000c01v1Entry 223 }

		-- 1.3.6.1.4.1.10106.3.101291.1.1.225
		tsa3000c01v1Tx1UniEna OBJECT-TYPE
			SYNTAX Bit0No1Yes
			MAX-ACCESS read-write
			STATUS current
			DESCRIPTION
				"Enable TX"
		::= { tsa3000c01v1Entry 225 }

		-- 1.3.6.1.4.1.10106.3.101291.1.1.227
		tsa3000c01v1Tx1MultiEna OBJECT-TYPE
			SYNTAX IpaTxMode
			MAX-ACCESS read-write
			STATUS current
			DESCRIPTION
				"TX mode"
		::= { tsa3000c01v1Entry 227 }

		-- 1.3.6.1.4.1.10106.3.101291.1.1.229
		tsa3000c01v1Tx1UipAdd3 OBJECT-TYPE
			SYNTAX Uint8
			MAX-ACCESS read-write
			STATUS current
			DESCRIPTION
				"Destination IP address (3)"
		::= { tsa3000c01v1Entry 229 }

		-- 1.3.6.1.4.1.10106.3.101291.1.1.231
		tsa3000c01v1Tx1UipAdd2 OBJECT-TYPE
			SYNTAX Uint8
			MAX-ACCESS read-write
			STATUS current
			DESCRIPTION
				"Destination IP address (2)"
		::= { tsa3000c01v1Entry 231 }

		-- 1.3.6.1.4.1.10106.3.101291.1.1.233
		tsa3000c01v1Tx1UipAdd1 OBJECT-TYPE
			SYNTAX Uint8
			MAX-ACCESS read-write
			STATUS current
			DESCRIPTION
				"Destination IP address (1)"
		::= { tsa3000c01v1Entry 233 }

		-- 1.3.6.1.4.1.10106.3.101291.1.1.235
		tsa3000c01v1Tx1UipAdd0 OBJECT-TYPE
			SYNTAX Uint8
			MAX-ACCESS read-write
			STATUS current
			DESCRIPTION
				"Destination IP address (0)"
		::= { tsa3000c01v1Entry 235 }

		-- 1.3.6.1.4.1.10106.3.101291.1.1.237
		tsa3000c01v1Tx1MipAdd3 OBJECT-TYPE
			SYNTAX Uint8
			MAX-ACCESS read-write
			STATUS current
			DESCRIPTION
				"Multicast dest. IP address (3)"
		::= { tsa3000c01v1Entry 237 }

		-- 1.3.6.1.4.1.10106.3.101291.1.1.239
		tsa3000c01v1Tx1MipAdd2 OBJECT-TYPE
			SYNTAX Uint8
			MAX-ACCESS read-write
			STATUS current
			DESCRIPTION
				"Multicast dest. IP address (2)"
		::= { tsa3000c01v1Entry 239 }

		-- 1.3.6.1.4.1.10106.3.101291.1.1.241
		tsa3000c01v1Tx1MipAdd1 OBJECT-TYPE
			SYNTAX Uint8
			MAX-ACCESS read-write
			STATUS current
			DESCRIPTION
				"Multicast dest. IP address (1)"
		::= { tsa3000c01v1Entry 241 }

		-- 1.3.6.1.4.1.10106.3.101291.1.1.243
		tsa3000c01v1Tx1MipAdd0 OBJECT-TYPE
			SYNTAX Uint8
			MAX-ACCESS read-write
			STATUS current
			DESCRIPTION
				"Multicast dest. IP address (0)"
		::= { tsa3000c01v1Entry 243 }

		-- 1.3.6.1.4.1.10106.3.101291.1.1.245
		tsa3000c01v1Tx1SPort OBJECT-TYPE
			SYNTAX Uint16
			MAX-ACCESS read-write
			STATUS current
			DESCRIPTION
				"Source port"
		::= { tsa3000c01v1Entry 245 }

		-- 1.3.6.1.4.1.10106.3.101291.1.1.247
		tsa3000c01v1Tx1DPort OBJECT-TYPE
			SYNTAX Uint16
			MAX-ACCESS read-write
			STATUS current
			DESCRIPTION
				"Destination port"
		::= { tsa3000c01v1Entry 247 }

		-- 1.3.6.1.4.1.10106.3.101291.1.1.249
		tsa3000c01v1VlanTxEnable1 OBJECT-TYPE
			SYNTAX Bit0No1Yes
			MAX-ACCESS read-write
			STATUS current
			DESCRIPTION
				"VLAN Enable"
		::= { tsa3000c01v1Entry 249 }

		-- 1.3.6.1.4.1.10106.3.101291.1.1.251
		tsa3000c01v1VlanTxPrior1 OBJECT-TYPE
			SYNTAX Uint3
			MAX-ACCESS read-write
			STATUS current
			DESCRIPTION
				"VLAN Priority"
		::= { tsa3000c01v1Entry 251 }

		-- 1.3.6.1.4.1.10106.3.101291.1.1.253
		tsa3000c01v1VlanTxId1 OBJECT-TYPE
			SYNTAX Uint12
			MAX-ACCESS read-write
			STATUS current
			DESCRIPTION
				"VLAN ID"
		::= { tsa3000c01v1Entry 253 }

		-- 1.3.6.1.4.1.10106.3.101291.1.1.255
		tsa3000c01v1Tx1LParam OBJECT-TYPE
			SYNTAX Uint5
			MAX-ACCESS read-write
			STATUS current
			DESCRIPTION
				"L parameter (FEC mode columns)"
		::= { tsa3000c01v1Entry 255 }

		-- 1.3.6.1.4.1.10106.3.101291.1.1.257
		tsa3000c01v1Tx1FecMode OBJECT-TYPE
			SYNTAX FecMode
			MAX-ACCESS read-write
			STATUS current
			DESCRIPTION
				"Protocol"
		::= { tsa3000c01v1Entry 257 }

		-- 1.3.6.1.4.1.10106.3.101291.1.1.259
		tsa3000c01v1Tx1DParam OBJECT-TYPE
			SYNTAX Uint5
			MAX-ACCESS read-write
			STATUS current
			DESCRIPTION
				"D parameter (FEC mode rows)"
		::= { tsa3000c01v1Entry 259 }

		-- 1.3.6.1.4.1.10106.3.101291.1.1.261
		tsa3000c01v1Tx1TspkInIppk OBJECT-TYPE
			SYNTAX Uint3
			MAX-ACCESS read-write
			STATUS current
			DESCRIPTION
				"TS packets in each IP packet"
		::= { tsa3000c01v1Entry 261 }

		-- 1.3.6.1.4.1.10106.3.101291.1.1.263
		tsa3000c01v1Tx1RowDelay OBJECT-TYPE
			SYNTAX Uint5
			MAX-ACCESS read-write
			STATUS current
			DESCRIPTION
				"FEC row delay"
		::= { tsa3000c01v1Entry 263 }

		-- 1.3.6.1.4.1.10106.3.101291.1.1.265
		tsa3000c01v1Tx1ColDelay OBJECT-TYPE
			SYNTAX Uint8
			MAX-ACCESS read-write
			STATUS current
			DESCRIPTION
				"FEC column delay"
		::= { tsa3000c01v1Entry 265 }

		-- 1.3.6.1.4.1.10106.3.101291.1.1.267
		tsa3000c01v1LowCost1 OBJECT-TYPE
			SYNTAX Bit0No1Yes
			MAX-ACCESS read-write
			STATUS current
			DESCRIPTION
				"TOS.  Low cost"
		::= { tsa3000c01v1Entry 267 }

		-- 1.3.6.1.4.1.10106.3.101291.1.1.269
		tsa3000c01v1HighReliab1 OBJECT-TYPE
			SYNTAX Bit0No1Yes
			MAX-ACCESS read-write
			STATUS current
			DESCRIPTION
				"TOS. High reliability"
		::= { tsa3000c01v1Entry 269 }

		-- 1.3.6.1.4.1.10106.3.101291.1.1.271
		tsa3000c01v1HighThroughp1 OBJECT-TYPE
			SYNTAX Bit0No1Yes
			MAX-ACCESS read-write
			STATUS current
			DESCRIPTION
				"TOS. High Throughput"
		::= { tsa3000c01v1Entry 271 }

		-- 1.3.6.1.4.1.10106.3.101291.1.1.273
		tsa3000c01v1LowDelay1 OBJECT-TYPE
			SYNTAX Bit0No1Yes
			MAX-ACCESS read-write
			STATUS current
			DESCRIPTION
				"TOS. Low delay"
		::= { tsa3000c01v1Entry 273 }

		-- 1.3.6.1.4.1.10106.3.101291.1.1.275
		tsa3000c01v1Precedence1 OBJECT-TYPE
			SYNTAX IpaPrecedence
			MAX-ACCESS read-write
			STATUS current
			DESCRIPTION
				"TOS. Precedence"
		::= { tsa3000c01v1Entry 275 }

		-- 1.3.6.1.4.1.10106.3.101291.1.1.277
		tsa3000c01v1Ttl1 OBJECT-TYPE
			SYNTAX Uint8
			MAX-ACCESS read-write
			STATUS current
			DESCRIPTION
				"Time to live"
		::= { tsa3000c01v1Entry 277 }

		-- 1.3.6.1.4.1.10106.3.101291.1.1.279
		tsa3000c01v1Str1IgmFAdd3 OBJECT-TYPE
			SYNTAX Uint8
			MAX-ACCESS read-write
			STATUS current
			DESCRIPTION
				"Source IP address (3)"
		::= { tsa3000c01v1Entry 279 }

		-- 1.3.6.1.4.1.10106.3.101291.1.1.281
		tsa3000c01v1Str1IgmFAdd2 OBJECT-TYPE
			SYNTAX Uint8
			MAX-ACCESS read-write
			STATUS current
			DESCRIPTION
				"Source IP address (2)"
		::= { tsa3000c01v1Entry 281 }

		-- 1.3.6.1.4.1.10106.3.101291.1.1.283
		tsa3000c01v1Str1IgmFAdd1 OBJECT-TYPE
			SYNTAX Uint8
			MAX-ACCESS read-write
			STATUS current
			DESCRIPTION
				"Source IP address (1)"
		::= { tsa3000c01v1Entry 283 }

		-- 1.3.6.1.4.1.10106.3.101291.1.1.285
		tsa3000c01v1Str1IgmFAdd0 OBJECT-TYPE
			SYNTAX Uint8
			MAX-ACCESS read-write
			STATUS current
			DESCRIPTION
				"Source IP address (0)"
		::= { tsa3000c01v1Entry 285 }

		-- 1.3.6.1.4.1.10106.3.101291.1.1.287
		tsa3000c01v1Str2IgmFAdd3 OBJECT-TYPE
			SYNTAX Uint8
			MAX-ACCESS read-write
			STATUS current
			DESCRIPTION
				"Source IP address (3)"
		::= { tsa3000c01v1Entry 287 }

		-- 1.3.6.1.4.1.10106.3.101291.1.1.289
		tsa3000c01v1Str2IgmFAdd2 OBJECT-TYPE
			SYNTAX Uint8
			MAX-ACCESS read-write
			STATUS current
			DESCRIPTION
				"Source IP address (2)"
		::= { tsa3000c01v1Entry 289 }

		-- 1.3.6.1.4.1.10106.3.101291.1.1.291
		tsa3000c01v1Str2IgmFAdd1 OBJECT-TYPE
			SYNTAX Uint8
			MAX-ACCESS read-write
			STATUS current
			DESCRIPTION
				"Source IP address (1)"
		::= { tsa3000c01v1Entry 291 }

		-- 1.3.6.1.4.1.10106.3.101291.1.1.293
		tsa3000c01v1Str2IgmFAdd0 OBJECT-TYPE
			SYNTAX Uint8
			MAX-ACCESS read-write
			STATUS current
			DESCRIPTION
				"Source IP address (0)"
		::= { tsa3000c01v1Entry 293 }

		-- 1.3.6.1.4.1.10106.3.101291.1.1.295
		tsa3000c01v1PmtPrgm0 OBJECT-TYPE
			SYNTAX Uint16
			MAX-ACCESS read-write
			STATUS current
			DESCRIPTION
				"Program for filter 1"
		::= { tsa3000c01v1Entry 295 }

		-- 1.3.6.1.4.1.10106.3.101291.1.1.297
		tsa3000c01v1PmtPrgm1 OBJECT-TYPE
			SYNTAX Uint16
			MAX-ACCESS read-write
			STATUS current
			DESCRIPTION
				"Program for filter 2"
		::= { tsa3000c01v1Entry 297 }

		-- 1.3.6.1.4.1.10106.3.101291.1.1.299
		tsa3000c01v1PmtPrgm2 OBJECT-TYPE
			SYNTAX Uint16
			MAX-ACCESS read-write
			STATUS current
			DESCRIPTION
				"Program for filter 3"
		::= { tsa3000c01v1Entry 299 }

		-- 1.3.6.1.4.1.10106.3.101291.1.1.301
		tsa3000c01v1PmtPrgm3 OBJECT-TYPE
			SYNTAX Uint16
			MAX-ACCESS read-write
			STATUS current
			DESCRIPTION
				"Program for filter 4"
		::= { tsa3000c01v1Entry 301 }

		-- 1.3.6.1.4.1.10106.3.101291.1.1.303
		tsa3000c01v1PmtPrgm4 OBJECT-TYPE
			SYNTAX Uint16
			MAX-ACCESS read-write
			STATUS current
			DESCRIPTION
				"Program for filter 5"
		::= { tsa3000c01v1Entry 303 }

		-- 1.3.6.1.4.1.10106.3.101291.1.1.305
		tsa3000c01v1PmtPrgm5 OBJECT-TYPE
			SYNTAX Uint16
			MAX-ACCESS read-write
			STATUS current
			DESCRIPTION
				"Program for filter 6"
		::= { tsa3000c01v1Entry 305 }

		-- 1.3.6.1.4.1.10106.3.101291.1.1.307
		tsa3000c01v1PmtPrgm6 OBJECT-TYPE
			SYNTAX Uint16
			MAX-ACCESS read-write
			STATUS current
			DESCRIPTION
				"Program for filter 7"
		::= { tsa3000c01v1Entry 307 }

		-- 1.3.6.1.4.1.10106.3.101291.1.1.309
		tsa3000c01v1PmtPrgm7 OBJECT-TYPE
			SYNTAX Uint16
			MAX-ACCESS read-write
			STATUS current
			DESCRIPTION
				"Program for filter 8"
		::= { tsa3000c01v1Entry 309 }

		-- 1.3.6.1.4.1.10106.3.101291.1.1.311
		tsa3000c01v1PmtPrgm8 OBJECT-TYPE
			SYNTAX Uint16
			MAX-ACCESS read-write
			STATUS current
			DESCRIPTION
				"Program for filter 9"
		::= { tsa3000c01v1Entry 311 }

		-- 1.3.6.1.4.1.10106.3.101291.1.1.313
		tsa3000c01v1PmtPrgm9 OBJECT-TYPE
			SYNTAX Uint16
			MAX-ACCESS read-write
			STATUS current
			DESCRIPTION
				"Program for filter 10"
		::= { tsa3000c01v1Entry 313 }

		-- 1.3.6.1.4.1.10106.3.101291.1.1.315
		tsa3000c01v1PmtPrgm10 OBJECT-TYPE
			SYNTAX Uint16
			MAX-ACCESS read-write
			STATUS current
			DESCRIPTION
				"Program for filter 11"
		::= { tsa3000c01v1Entry 315 }

		-- 1.3.6.1.4.1.10106.3.101291.1.1.317
		tsa3000c01v1PmtPrgm11 OBJECT-TYPE
			SYNTAX Uint16
			MAX-ACCESS read-write
			STATUS current
			DESCRIPTION
				"Program for filter 12"
		::= { tsa3000c01v1Entry 317 }

		-- 1.3.6.1.4.1.10106.3.101291.1.1.319
		tsa3000c01v1PmtPrgm12 OBJECT-TYPE
			SYNTAX Uint16
			MAX-ACCESS read-write
			STATUS current
			DESCRIPTION
				"Program for filter 13"
		::= { tsa3000c01v1Entry 319 }

		-- 1.3.6.1.4.1.10106.3.101291.1.1.321
		tsa3000c01v1PmtPrgm13 OBJECT-TYPE
			SYNTAX Uint16
			MAX-ACCESS read-write
			STATUS current
			DESCRIPTION
				"Program for filter 14"
		::= { tsa3000c01v1Entry 321 }

		-- 1.3.6.1.4.1.10106.3.101291.1.1.323
		tsa3000c01v1PmtPrgm14 OBJECT-TYPE
			SYNTAX Uint16
			MAX-ACCESS read-write
			STATUS current
			DESCRIPTION
				"Program for filter 15"
		::= { tsa3000c01v1Entry 323 }

		-- 1.3.6.1.4.1.10106.3.101291.1.1.325
		tsa3000c01v1PmtPrgm15 OBJECT-TYPE
			SYNTAX Uint16
			MAX-ACCESS read-write
			STATUS current
			DESCRIPTION
				"Program for filter 16"
		::= { tsa3000c01v1Entry 325 }

		-- 1.3.6.1.4.1.10106.3.101291.1.1.327
		tsa3000c01v1Str1AipDAdd3 OBJECT-TYPE
			SYNTAX Uint8
			MAX-ACCESS read-write
			STATUS current
			DESCRIPTION
				"Alternative multicast IP address (3)"
		::= { tsa3000c01v1Entry 327 }

		-- 1.3.6.1.4.1.10106.3.101291.1.1.329
		tsa3000c01v1Str1AipDAdd2 OBJECT-TYPE
			SYNTAX Uint8
			MAX-ACCESS read-write
			STATUS current
			DESCRIPTION
				"Alternative multicast IP address (2)"
		::= { tsa3000c01v1Entry 329 }

		-- 1.3.6.1.4.1.10106.3.101291.1.1.331
		tsa3000c01v1Str1AipDAdd1 OBJECT-TYPE
			SYNTAX Uint8
			MAX-ACCESS read-write
			STATUS current
			DESCRIPTION
				"Alternative multicast IP address (3)Alternative multicast IP address (1)"
		::= { tsa3000c01v1Entry 331 }

		-- 1.3.6.1.4.1.10106.3.101291.1.1.333
		tsa3000c01v1Str1AipDAdd0 OBJECT-TYPE
			SYNTAX Uint8
			MAX-ACCESS read-write
			STATUS current
			DESCRIPTION
				"Alternative multicast IP address (0)"
		::= { tsa3000c01v1Entry 333 }

		-- 1.3.6.1.4.1.10106.3.101291.1.1.335
		tsa3000c01v1Str1APortMsb OBJECT-TYPE
			SYNTAX Uint8
			MAX-ACCESS read-write
			STATUS current
			DESCRIPTION
				"Alternative destination port (msb)"
		::= { tsa3000c01v1Entry 335 }

		-- 1.3.6.1.4.1.10106.3.101291.1.1.337
		tsa3000c01v1Str1APortLsb OBJECT-TYPE
			SYNTAX Uint8
			MAX-ACCESS read-write
			STATUS current
			DESCRIPTION
				"Alternative destination port (lsb)"
		::= { tsa3000c01v1Entry 337 }

		-- 1.3.6.1.4.1.10106.3.101291.1.1.339
		tsa3000c01v1Str1IgmAAdd3 OBJECT-TYPE
			SYNTAX Uint8
			MAX-ACCESS read-write
			STATUS current
			DESCRIPTION
				"Alternative source IP address (3)"
		::= { tsa3000c01v1Entry 339 }

		-- 1.3.6.1.4.1.10106.3.101291.1.1.341
		tsa3000c01v1Str1IgmAAdd2 OBJECT-TYPE
			SYNTAX Uint8
			MAX-ACCESS read-write
			STATUS current
			DESCRIPTION
				"Alternative source IP address (2)"
		::= { tsa3000c01v1Entry 341 }

		-- 1.3.6.1.4.1.10106.3.101291.1.1.343
		tsa3000c01v1Str1IgmAAdd1 OBJECT-TYPE
			SYNTAX Uint8
			MAX-ACCESS read-write
			STATUS current
			DESCRIPTION
				"Alternative source IP address (1)"
		::= { tsa3000c01v1Entry 343 }

		-- 1.3.6.1.4.1.10106.3.101291.1.1.345
		tsa3000c01v1Str1IgmAAdd0 OBJECT-TYPE
			SYNTAX Uint8
			MAX-ACCESS read-write
			STATUS current
			DESCRIPTION
				"Alternative source IP address (0)"
		::= { tsa3000c01v1Entry 345 }

		-- 1.3.6.1.4.1.10106.3.101291.1.1.347
		tsa3000c01v1Str2AipDAdd3 OBJECT-TYPE
			SYNTAX Uint8
			MAX-ACCESS read-write
			STATUS current
			DESCRIPTION
				"Alternative multicast IP address (3)"
		::= { tsa3000c01v1Entry 347 }

		-- 1.3.6.1.4.1.10106.3.101291.1.1.349
		tsa3000c01v1Str2AipDAdd2 OBJECT-TYPE
			SYNTAX Uint8
			MAX-ACCESS read-write
			STATUS current
			DESCRIPTION
				"Alternative multicast IP address (2)"
		::= { tsa3000c01v1Entry 349 }

		-- 1.3.6.1.4.1.10106.3.101291.1.1.351
		tsa3000c01v1Str2AipDAdd1 OBJECT-TYPE
			SYNTAX Uint8
			MAX-ACCESS read-write
			STATUS current
			DESCRIPTION
				"Alternative multicast IP address (1)"
		::= { tsa3000c01v1Entry 351 }

		-- 1.3.6.1.4.1.10106.3.101291.1.1.353
		tsa3000c01v1Str2AipDAdd0 OBJECT-TYPE
			SYNTAX Uint8
			MAX-ACCESS read-write
			STATUS current
			DESCRIPTION
				"Alternative multicast IP address (0)"
		::= { tsa3000c01v1Entry 353 }

		-- 1.3.6.1.4.1.10106.3.101291.1.1.355
		tsa3000c01v1Str2APortMsb OBJECT-TYPE
			SYNTAX Uint8
			MAX-ACCESS read-write
			STATUS current
			DESCRIPTION
				"Alternative destination port (msb)"
		::= { tsa3000c01v1Entry 355 }

		-- 1.3.6.1.4.1.10106.3.101291.1.1.357
		tsa3000c01v1Str2APortLsb OBJECT-TYPE
			SYNTAX Uint8
			MAX-ACCESS read-write
			STATUS current
			DESCRIPTION
				"Alternative destination port (lsb)"
		::= { tsa3000c01v1Entry 357 }

		-- 1.3.6.1.4.1.10106.3.101291.1.1.359
		tsa3000c01v1Str2IgmAAdd3 OBJECT-TYPE
			SYNTAX Uint8
			MAX-ACCESS read-write
			STATUS current
			DESCRIPTION
				"Alternative source IP address (3)"
		::= { tsa3000c01v1Entry 359 }

		-- 1.3.6.1.4.1.10106.3.101291.1.1.361
		tsa3000c01v1Str2IgmAAdd2 OBJECT-TYPE
			SYNTAX Uint8
			MAX-ACCESS read-write
			STATUS current
			DESCRIPTION
				"Alternative source IP address (2)"
		::= { tsa3000c01v1Entry 361 }

		-- 1.3.6.1.4.1.10106.3.101291.1.1.363
		tsa3000c01v1Str2IgmAAdd1 OBJECT-TYPE
			SYNTAX Uint8
			MAX-ACCESS read-write
			STATUS current
			DESCRIPTION
				"Alternative source IP address (1)"
		::= { tsa3000c01v1Entry 363 }

		-- 1.3.6.1.4.1.10106.3.101291.1.1.365
		tsa3000c01v1Str2IgmAAdd0 OBJECT-TYPE
			SYNTAX Uint8
			MAX-ACCESS read-write
			STATUS current
			DESCRIPTION
				"Alternative source IP address (0)"
		::= { tsa3000c01v1Entry 365 }

		-- 1.3.6.1.4.1.10106.3.101291.1.1.367
		tsa3000c01v1PidPacket0 OBJECT-TYPE
			SYNTAX Uint13
			MAX-ACCESS read-write
			STATUS current
			DESCRIPTION
				"Preserved PID 1"
		::= { tsa3000c01v1Entry 367 }

		-- 1.3.6.1.4.1.10106.3.101291.1.1.369
		tsa3000c01v1PidPacket1 OBJECT-TYPE
			SYNTAX Uint13
			MAX-ACCESS read-write
			STATUS current
			DESCRIPTION
				"Preserved PID 2"
		::= { tsa3000c01v1Entry 369 }

		-- 1.3.6.1.4.1.10106.3.101291.1.1.371
		tsa3000c01v1PidPacket2 OBJECT-TYPE
			SYNTAX Uint13
			MAX-ACCESS read-write
			STATUS current
			DESCRIPTION
				"Preserved PID 3"
		::= { tsa3000c01v1Entry 371 }

		-- 1.3.6.1.4.1.10106.3.101291.1.1.373
		tsa3000c01v1PidPacket3 OBJECT-TYPE
			SYNTAX Uint13
			MAX-ACCESS read-write
			STATUS current
			DESCRIPTION
				"Preserved PID 4"
		::= { tsa3000c01v1Entry 373 }

		-- 1.3.6.1.4.1.10106.3.101291.1.1.375
		tsa3000c01v1PidPacket4 OBJECT-TYPE
			SYNTAX Uint13
			MAX-ACCESS read-write
			STATUS current
			DESCRIPTION
				"Preserved PID 5"
		::= { tsa3000c01v1Entry 375 }

		-- 1.3.6.1.4.1.10106.3.101291.1.1.377
		tsa3000c01v1PidPacket5 OBJECT-TYPE
			SYNTAX Uint13
			MAX-ACCESS read-write
			STATUS current
			DESCRIPTION
				"Preserved PID 6"
		::= { tsa3000c01v1Entry 377 }

		-- 1.3.6.1.4.1.10106.3.101291.1.1.379
		tsa3000c01v1PidPacket6 OBJECT-TYPE
			SYNTAX Uint13
			MAX-ACCESS read-write
			STATUS current
			DESCRIPTION
				"Preserved PID 7"
		::= { tsa3000c01v1Entry 379 }

		-- 1.3.6.1.4.1.10106.3.101291.1.1.381
		tsa3000c01v1PidPacket7 OBJECT-TYPE
			SYNTAX Uint13
			MAX-ACCESS read-write
			STATUS current
			DESCRIPTION
				"Preserved PID 8"
		::= { tsa3000c01v1Entry 381 }

		-- 1.3.6.1.4.1.10106.3.101291.1.1.383
		tsa3000c01v1PidPacket8 OBJECT-TYPE
			SYNTAX Uint13
			MAX-ACCESS read-write
			STATUS current
			DESCRIPTION
				"Preserved PID 9"
		::= { tsa3000c01v1Entry 383 }

		-- 1.3.6.1.4.1.10106.3.101291.1.1.385
		tsa3000c01v1PidPacket9 OBJECT-TYPE
			SYNTAX Uint13
			MAX-ACCESS read-write
			STATUS current
			DESCRIPTION
				"Preserved PID 10"
		::= { tsa3000c01v1Entry 385 }

		-- 1.3.6.1.4.1.10106.3.101291.1.1.387
		tsa3000c01v1PidPacket10 OBJECT-TYPE
			SYNTAX Uint13
			MAX-ACCESS read-write
			STATUS current
			DESCRIPTION
				"Preserved PID 11"
		::= { tsa3000c01v1Entry 387 }

		-- 1.3.6.1.4.1.10106.3.101291.1.1.389
		tsa3000c01v1PidPacket11 OBJECT-TYPE
			SYNTAX Uint13
			MAX-ACCESS read-write
			STATUS current
			DESCRIPTION
				"Preserved PID 12"
		::= { tsa3000c01v1Entry 389 }

		-- 1.3.6.1.4.1.10106.3.101291.1.1.391
		tsa3000c01v1PidPacket12 OBJECT-TYPE
			SYNTAX Uint13
			MAX-ACCESS read-write
			STATUS current
			DESCRIPTION
				"Preserved PID 13"
		::= { tsa3000c01v1Entry 391 }

		-- 1.3.6.1.4.1.10106.3.101291.1.1.393
		tsa3000c01v1PidPacket13 OBJECT-TYPE
			SYNTAX Uint13
			MAX-ACCESS read-write
			STATUS current
			DESCRIPTION
				"Preserved PID 14"
		::= { tsa3000c01v1Entry 393 }

		-- 1.3.6.1.4.1.10106.3.101291.1.1.395
		tsa3000c01v1PidPacket14 OBJECT-TYPE
			SYNTAX Uint13
			MAX-ACCESS read-write
			STATUS current
			DESCRIPTION
				"Preserved PID 15"
		::= { tsa3000c01v1Entry 395 }

		-- 1.3.6.1.4.1.10106.3.101291.1.1.397
		tsa3000c01v1PidPacket15 OBJECT-TYPE
			SYNTAX Uint13
			MAX-ACCESS read-write
			STATUS current
			DESCRIPTION
				"Preserved PID 16"
		::= { tsa3000c01v1Entry 397 }

		-- 1.3.6.1.4.1.10106.3.101291.1.1.399
		tsa3000c01v1PatStat OBJECT-TYPE
			SYNTAX TableAnalStat
			MAX-ACCESS read-only
			STATUS current
			DESCRIPTION
				"PAT analyzer status"
		::= { tsa3000c01v1Entry 399 }

		-- 1.3.6.1.4.1.10106.3.101291.1.1.401
		tsa3000c01v1CatStat OBJECT-TYPE
			SYNTAX TableAnalStat
			MAX-ACCESS read-only
			STATUS current
			DESCRIPTION
				"CAT analyzer status"
		::= { tsa3000c01v1Entry 401 }

		-- 1.3.6.1.4.1.10106.3.101291.1.1.403
		tsa3000c01v1PmtPrgmStat0 OBJECT-TYPE
			SYNTAX TableAnalStat
			MAX-ACCESS read-only
			STATUS current
			DESCRIPTION
				"Program filter 1 status"
		::= { tsa3000c01v1Entry 403 }

		-- 1.3.6.1.4.1.10106.3.101291.1.1.405
		tsa3000c01v1PmtPrgmStat1 OBJECT-TYPE
			SYNTAX TableAnalStat
			MAX-ACCESS read-only
			STATUS current
			DESCRIPTION
				"Program filter 2 status"
		::= { tsa3000c01v1Entry 405 }

		-- 1.3.6.1.4.1.10106.3.101291.1.1.407
		tsa3000c01v1PmtPrgmStat2 OBJECT-TYPE
			SYNTAX TableAnalStat
			MAX-ACCESS read-only
			STATUS current
			DESCRIPTION
				"Program filter 3 status"
		::= { tsa3000c01v1Entry 407 }

		-- 1.3.6.1.4.1.10106.3.101291.1.1.409
		tsa3000c01v1PmtPrgmStat3 OBJECT-TYPE
			SYNTAX TableAnalStat
			MAX-ACCESS read-only
			STATUS current
			DESCRIPTION
				"Program filter 4 status"
		::= { tsa3000c01v1Entry 409 }

		-- 1.3.6.1.4.1.10106.3.101291.1.1.411
		tsa3000c01v1PmtPrgmStat4 OBJECT-TYPE
			SYNTAX TableAnalStat
			MAX-ACCESS read-only
			STATUS current
			DESCRIPTION
				"Program filter 5 status"
		::= { tsa3000c01v1Entry 411 }

		-- 1.3.6.1.4.1.10106.3.101291.1.1.413
		tsa3000c01v1PmtPrgmStat5 OBJECT-TYPE
			SYNTAX TableAnalStat
			MAX-ACCESS read-only
			STATUS current
			DESCRIPTION
				"Program filter 6 status"
		::= { tsa3000c01v1Entry 413 }

		-- 1.3.6.1.4.1.10106.3.101291.1.1.415
		tsa3000c01v1PmtPrgmStat6 OBJECT-TYPE
			SYNTAX TableAnalStat
			MAX-ACCESS read-only
			STATUS current
			DESCRIPTION
				"Program filter 7 status"
		::= { tsa3000c01v1Entry 415 }

		-- 1.3.6.1.4.1.10106.3.101291.1.1.417
		tsa3000c01v1PmtPrgmStat7 OBJECT-TYPE
			SYNTAX TableAnalStat
			MAX-ACCESS read-only
			STATUS current
			DESCRIPTION
				"Program filter 8 status"
		::= { tsa3000c01v1Entry 417 }

		-- 1.3.6.1.4.1.10106.3.101291.1.1.419
		tsa3000c01v1PmtPrgmStat8 OBJECT-TYPE
			SYNTAX TableAnalStat
			MAX-ACCESS read-only
			STATUS current
			DESCRIPTION
				"Program filter 9 status"
		::= { tsa3000c01v1Entry 419 }

		-- 1.3.6.1.4.1.10106.3.101291.1.1.421
		tsa3000c01v1PmtPrgmStat9 OBJECT-TYPE
			SYNTAX TableAnalStat
			MAX-ACCESS read-only
			STATUS current
			DESCRIPTION
				"Program filter 10 status"
		::= { tsa3000c01v1Entry 421 }

		-- 1.3.6.1.4.1.10106.3.101291.1.1.423
		tsa3000c01v1PmtPrgmStat10 OBJECT-TYPE
			SYNTAX TableAnalStat
			MAX-ACCESS read-only
			STATUS current
			DESCRIPTION
				"Program filter 11 status"
		::= { tsa3000c01v1Entry 423 }

		-- 1.3.6.1.4.1.10106.3.101291.1.1.425
		tsa3000c01v1PmtPrgmStat11 OBJECT-TYPE
			SYNTAX TableAnalStat
			MAX-ACCESS read-only
			STATUS current
			DESCRIPTION
				"Program filter 12 status"
		::= { tsa3000c01v1Entry 425 }

		-- 1.3.6.1.4.1.10106.3.101291.1.1.427
		tsa3000c01v1PmtPrgmStat12 OBJECT-TYPE
			SYNTAX TableAnalStat
			MAX-ACCESS read-only
			STATUS current
			DESCRIPTION
				"Program filter 13 status"
		::= { tsa3000c01v1Entry 427 }

		-- 1.3.6.1.4.1.10106.3.101291.1.1.429
		tsa3000c01v1PmtPrgmStat13 OBJECT-TYPE
			SYNTAX TableAnalStat
			MAX-ACCESS read-only
			STATUS current
			DESCRIPTION
				"Program filter 14 status"
		::= { tsa3000c01v1Entry 429 }

		-- 1.3.6.1.4.1.10106.3.101291.1.1.431
		tsa3000c01v1PmtPrgmStat14 OBJECT-TYPE
			SYNTAX TableAnalStat
			MAX-ACCESS read-only
			STATUS current
			DESCRIPTION
				"Program filter 15 status"
		::= { tsa3000c01v1Entry 431 }

		-- 1.3.6.1.4.1.10106.3.101291.1.1.433
		tsa3000c01v1PmtPrgmStat15 OBJECT-TYPE
			SYNTAX TableAnalStat
			MAX-ACCESS read-only
			STATUS current
			DESCRIPTION
				"Program filter 16 status"
		::= { tsa3000c01v1Entry 433 }

		-- 1.3.6.1.4.1.10106.3.101291.1.1.435
		tsa3000c01v1BitrateUtil OBJECT-TYPE
			SYNTAX BitrateRead
			MAX-ACCESS read-only
			STATUS current
			DESCRIPTION
				"Measured output bitrate after filtering"
		::= { tsa3000c01v1Entry 435 }

		-- 1.3.6.1.4.1.10106.3.101291.1.1.437
		tsa3000c01v1OutFail OBJECT-TYPE
			SYNTAX BitFail
			MAX-ACCESS read-only
			STATUS current
			DESCRIPTION
				"The output signal is not valid because all inputs failed"
		::= { tsa3000c01v1Entry 437 }

		-- 1.3.6.1.4.1.10106.3.101291.1.1.439
		tsa3000c01v1AsiIn1Fail OBJECT-TYPE
			SYNTAX BitFail
			MAX-ACCESS read-only
			STATUS current
			DESCRIPTION
				"ASI IN 1 fail status"
		::= { tsa3000c01v1Entry 439 }

		-- 1.3.6.1.4.1.10106.3.101291.1.1.440
		tsa3000c01v1AsiIn1FailTrapEnable OBJECT-TYPE
			SYNTAX AlarmEnable
			MAX-ACCESS read-write
			STATUS current
			DESCRIPTION
				"ASI IN 1 fail status Trap Enable"
		::= { tsa3000c01v1Entry 440 }

		-- 1.3.6.1.4.1.10106.3.101291.1.1.441
		tsa3000c01v1ExAsiIn1Fail OBJECT-TYPE
			SYNTAX BitFail
			MAX-ACCESS read-only
			STATUS current
			DESCRIPTION
				"ASI IN 1 external input fail status"
		::= { tsa3000c01v1Entry 441 }

		-- 1.3.6.1.4.1.10106.3.101291.1.1.442
		tsa3000c01v1ExAsiIn1FailTrapEnable OBJECT-TYPE
			SYNTAX AlarmEnable
			MAX-ACCESS read-write
			STATUS current
			DESCRIPTION
				"ASI IN 1 external input fail status Trap Enable"
		::= { tsa3000c01v1Entry 442 }

		-- 1.3.6.1.4.1.10106.3.101291.1.1.443
		tsa3000c01v1AsiIn2Fail OBJECT-TYPE
			SYNTAX BitFail
			MAX-ACCESS read-only
			STATUS current
			DESCRIPTION
				"ASI  IN 2 fail status"
		::= { tsa3000c01v1Entry 443 }

		-- 1.3.6.1.4.1.10106.3.101291.1.1.444
		tsa3000c01v1AsiIn2FailTrapEnable OBJECT-TYPE
			SYNTAX AlarmEnable
			MAX-ACCESS read-write
			STATUS current
			DESCRIPTION
				"ASI  IN 2 fail status Trap Enable"
		::= { tsa3000c01v1Entry 444 }

		-- 1.3.6.1.4.1.10106.3.101291.1.1.445
		tsa3000c01v1ExAsiIn2Fail OBJECT-TYPE
			SYNTAX BitFail
			MAX-ACCESS read-only
			STATUS current
			DESCRIPTION
				"ASI  IN 2 fail external input fail status"
		::= { tsa3000c01v1Entry 445 }

		-- 1.3.6.1.4.1.10106.3.101291.1.1.446
		tsa3000c01v1ExAsiIn2FailTrapEnable OBJECT-TYPE
			SYNTAX AlarmEnable
			MAX-ACCESS read-write
			STATUS current
			DESCRIPTION
				"ASI  IN 2 fail external input fail status Trap Enable"
		::= { tsa3000c01v1Entry 446 }

		-- 1.3.6.1.4.1.10106.3.101291.1.1.447
		tsa3000c01v1IpIn1Fail OBJECT-TYPE
			SYNTAX BitFail
			MAX-ACCESS read-only
			STATUS current
			DESCRIPTION
				"IP IN 1 fail status"
		::= { tsa3000c01v1Entry 447 }

		-- 1.3.6.1.4.1.10106.3.101291.1.1.448
		tsa3000c01v1IpIn1FailTrapEnable OBJECT-TYPE
			SYNTAX AlarmEnable
			MAX-ACCESS read-write
			STATUS current
			DESCRIPTION
				"IP IN 1 fail status Trap Enable"
		::= { tsa3000c01v1Entry 448 }

		-- 1.3.6.1.4.1.10106.3.101291.1.1.449
		tsa3000c01v1ExIpIn1Fail OBJECT-TYPE
			SYNTAX BitFail
			MAX-ACCESS read-only
			STATUS current
			DESCRIPTION
				"IP IN 1 external input fail status"
		::= { tsa3000c01v1Entry 449 }

		-- 1.3.6.1.4.1.10106.3.101291.1.1.450
		tsa3000c01v1ExIpIn1FailTrapEnable OBJECT-TYPE
			SYNTAX AlarmEnable
			MAX-ACCESS read-write
			STATUS current
			DESCRIPTION
				"IP IN 1 external input fail status Trap Enable"
		::= { tsa3000c01v1Entry 450 }

		-- 1.3.6.1.4.1.10106.3.101291.1.1.451
		tsa3000c01v1IpIn2Fail OBJECT-TYPE
			SYNTAX BitFail
			MAX-ACCESS read-only
			STATUS current
			DESCRIPTION
				"IP IN 2 input status"
		::= { tsa3000c01v1Entry 451 }

		-- 1.3.6.1.4.1.10106.3.101291.1.1.452
		tsa3000c01v1IpIn2FailTrapEnable OBJECT-TYPE
			SYNTAX AlarmEnable
			MAX-ACCESS read-write
			STATUS current
			DESCRIPTION
				"IP IN 2 input status Trap Enable"
		::= { tsa3000c01v1Entry 452 }

		-- 1.3.6.1.4.1.10106.3.101291.1.1.453
		tsa3000c01v1ExIpIn2Fail OBJECT-TYPE
			SYNTAX BitFail
			MAX-ACCESS read-only
			STATUS current
			DESCRIPTION
				"IP IN 2 external input fail status"
		::= { tsa3000c01v1Entry 453 }

		-- 1.3.6.1.4.1.10106.3.101291.1.1.454
		tsa3000c01v1ExIpIn2FailTrapEnable OBJECT-TYPE
			SYNTAX AlarmEnable
			MAX-ACCESS read-write
			STATUS current
			DESCRIPTION
				"IP IN 2 external input fail status Trap Enable"
		::= { tsa3000c01v1Entry 454 }

		-- 1.3.6.1.4.1.10106.3.101291.1.1.455
		tsa3000c01v1DestAvailable1 OBJECT-TYPE
			SYNTAX Bit0No1Yes
			MAX-ACCESS read-only
			STATUS current
			DESCRIPTION
				"Destination IP available"
		::= { tsa3000c01v1Entry 455 }

		-- 1.3.6.1.4.1.10106.3.101291.1.1.457
		tsa3000c01v1BlindModStat1 OBJECT-TYPE
			SYNTAX BlindModeStat
			MAX-ACCESS read-only
			STATUS current
			DESCRIPTION
				"Active receiver in blind mode"
		::= { tsa3000c01v1Entry 457 }

		-- 1.3.6.1.4.1.10106.3.101291.1.1.459
		tsa3000c01v1BlindModStat2 OBJECT-TYPE
			SYNTAX BlindModeStat
			MAX-ACCESS read-only
			STATUS current
			DESCRIPTION
				"Active receiver in blind mode"
		::= { tsa3000c01v1Entry 459 }

		-- 1.3.6.1.4.1.10106.3.101291.1.1.461
		tsa3000c01v1AsiIn1Delay OBJECT-TYPE
			SYNTAX DelayX131Ms
			MAX-ACCESS read-only
			STATUS current
			DESCRIPTION
				"ASI IN 1 to output delay"
		::= { tsa3000c01v1Entry 461 }

		-- 1.3.6.1.4.1.10106.3.101291.1.1.463
		tsa3000c01v1AsiIn2Delay OBJECT-TYPE
			SYNTAX DelayX131Ms
			MAX-ACCESS read-only
			STATUS current
			DESCRIPTION
				"ASI IN 2 to output delay"
		::= { tsa3000c01v1Entry 463 }

		-- 1.3.6.1.4.1.10106.3.101291.1.1.465
		tsa3000c01v1IpIn1Delay OBJECT-TYPE
			SYNTAX DelayX131Ms
			MAX-ACCESS read-only
			STATUS current
			DESCRIPTION
				"IP IN 1 to output delay"
		::= { tsa3000c01v1Entry 465 }

		-- 1.3.6.1.4.1.10106.3.101291.1.1.467
		tsa3000c01v1IpIn2Delay OBJECT-TYPE
			SYNTAX DelayX131Ms
			MAX-ACCESS read-only
			STATUS current
			DESCRIPTION
				"IP IN 2 to output delay"
		::= { tsa3000c01v1Entry 467 }

		-- 1.3.6.1.4.1.10106.3.101291.1.1.469
		tsa3000c01v1IpRxAddress3 OBJECT-TYPE
			SYNTAX Uint8
			MAX-ACCESS read-only
			STATUS current
			DESCRIPTION
				"RX packets source IP address (3)"
		::= { tsa3000c01v1Entry 469 }

		-- 1.3.6.1.4.1.10106.3.101291.1.1.471
		tsa3000c01v1IpRxAddress2 OBJECT-TYPE
			SYNTAX Uint8
			MAX-ACCESS read-only
			STATUS current
			DESCRIPTION
				"RX packets source IP address (2)"
		::= { tsa3000c01v1Entry 471 }

		-- 1.3.6.1.4.1.10106.3.101291.1.1.473
		tsa3000c01v1IpRxAddress1 OBJECT-TYPE
			SYNTAX Uint8
			MAX-ACCESS read-only
			STATUS current
			DESCRIPTION
				"RX packets source IP address (1)"
		::= { tsa3000c01v1Entry 473 }

		-- 1.3.6.1.4.1.10106.3.101291.1.1.475
		tsa3000c01v1IpRxAddress0 OBJECT-TYPE
			SYNTAX Uint8
			MAX-ACCESS read-only
			STATUS current
			DESCRIPTION
				"RX packets source IP address (0)"
		::= { tsa3000c01v1Entry 475 }

		-- 1.3.6.1.4.1.10106.3.101291.1.1.477
		tsa3000c01v1IpRxPort OBJECT-TYPE
			SYNTAX Uint16
			MAX-ACCESS read-only
			STATUS current
			DESCRIPTION
				"RX packets UDP source port"
		::= { tsa3000c01v1Entry 477 }

		-- 1.3.6.1.4.1.10106.3.101291.1.1.479
		tsa3000c01v1LParam OBJECT-TYPE
			SYNTAX Uint5
			MAX-ACCESS read-only
			STATUS current
			DESCRIPTION
				"L parameter (FEC mode columns)"
		::= { tsa3000c01v1Entry 479 }

		-- 1.3.6.1.4.1.10106.3.101291.1.1.481
		tsa3000c01v1FecMode OBJECT-TYPE
			SYNTAX FecMode
			MAX-ACCESS read-only
			STATUS current
			DESCRIPTION
				"Protocol"
		::= { tsa3000c01v1Entry 481 }

		-- 1.3.6.1.4.1.10106.3.101291.1.1.483
		tsa3000c01v1PacketSize OBJECT-TYPE
			SYNTAX Bit02041188
			MAX-ACCESS read-only
			STATUS current
			DESCRIPTION
				"Bytes in TS packets"
		::= { tsa3000c01v1Entry 483 }

		-- 1.3.6.1.4.1.10106.3.101291.1.1.485
		tsa3000c01v1DParam OBJECT-TYPE
			SYNTAX Uint5
			MAX-ACCESS read-only
			STATUS current
			DESCRIPTION
				"D parameter (FEC mode rows)"
		::= { tsa3000c01v1Entry 485 }

		-- 1.3.6.1.4.1.10106.3.101291.1.1.487
		tsa3000c01v1TsPckInIpPck OBJECT-TYPE
			SYNTAX Uint3
			MAX-ACCESS read-only
			STATUS current
			DESCRIPTION
				"TS packets in each IP packet"
		::= { tsa3000c01v1Entry 487 }

		-- 1.3.6.1.4.1.10106.3.101291.1.1.489
		tsa3000c01v1PacketRate OBJECT-TYPE
			SYNTAX PacketRate
			MAX-ACCESS read-only
			STATUS current
			DESCRIPTION
				"IP packet rate"
		::= { tsa3000c01v1Entry 489 }

		-- 1.3.6.1.4.1.10106.3.101291.1.1.491
		tsa3000c01v1TimeSinceReset OBJECT-TYPE
			SYNTAX TimeS4
			MAX-ACCESS read-only
			STATUS current
			DESCRIPTION
				"Elapsed time from last reset"
		::= { tsa3000c01v1Entry 491 }

		-- 1.3.6.1.4.1.10106.3.101291.1.1.493
		tsa3000c01v1LostIpPck OBJECT-TYPE
			SYNTAX Uint16
			MAX-ACCESS read-only
			STATUS current
			DESCRIPTION
				"Lost IP packets"
		::= { tsa3000c01v1Entry 493 }

		-- 1.3.6.1.4.1.10106.3.101291.1.1.495
		tsa3000c01v1RecoveredIpPck OBJECT-TYPE
			SYNTAX Uint16
			MAX-ACCESS read-only
			STATUS current
			DESCRIPTION
				"Recovered IP packets"
		::= { tsa3000c01v1Entry 495 }

		-- 1.3.6.1.4.1.10106.3.101291.1.1.497
		tsa3000c01v1OutOrdIpPck OBJECT-TYPE
			SYNTAX Uint16
			MAX-ACCESS read-only
			STATUS current
			DESCRIPTION
				"Out of order IP packets"
		::= { tsa3000c01v1Entry 497 }

		-- 1.3.6.1.4.1.10106.3.101291.1.1.499
		tsa3000c01v1FecRate OBJECT-TYPE
			SYNTAX PacketRate
			MAX-ACCESS read-only
			STATUS current
			DESCRIPTION
				"FEC packet rate"
		::= { tsa3000c01v1Entry 499 }

		-- 1.3.6.1.4.1.10106.3.101291.1.1.501
		tsa3000c01v1Link OBJECT-TYPE
			SYNTAX IpaEtherStat
			MAX-ACCESS read-only
			STATUS current
			DESCRIPTION
				"Ethernet conection status"
		::= { tsa3000c01v1Entry 501 }

		-- 1.3.6.1.4.1.10106.3.101291.1.1.502
		tsa3000c01v1LinkTrapEnable OBJECT-TYPE
			SYNTAX AlarmEnable
			MAX-ACCESS read-write
			STATUS current
			DESCRIPTION
				"Ethernet conection status Trap Enable"
		::= { tsa3000c01v1Entry 502 }

		-- 1.3.6.1.4.1.10106.3.101291.1.1.503
		tsa3000c01v1BufferStatus OBJECT-TYPE
			SYNTAX Rate1
			MAX-ACCESS read-only
			STATUS current
			DESCRIPTION
				"Buffer filling status in non DVB-T mode"
		::= { tsa3000c01v1Entry 503 }

		-- 1.3.6.1.4.1.10106.3.101291.1.1.505
		tsa3000c01v1PingStatus1 OBJECT-TYPE
			SYNTAX IpaPingStat
			MAX-ACCESS read-only
			STATUS current
			DESCRIPTION
				"Ping status"
		::= { tsa3000c01v1Entry 505 }

		-- 1.3.6.1.4.1.10106.3.101291.1.1.507
		tsa3000c01v1SerialNo OBJECT-TYPE
			SYNTAX SerialNo
			MAX-ACCESS read-only
			STATUS current
			DESCRIPTION
				"Serial number"
		::= { tsa3000c01v1Entry 507 }

		-- 1.3.6.1.4.1.10106.3.101291.1.1.509
		tsa3000c01v1SpeedForce OBJECT-TYPE
			SYNTAX Bit0Ann1For
			MAX-ACCESS read-write
			STATUS current
			DESCRIPTION
				"Allows selecting if the speed/mode is forced or announced for autonegotiation"
		::= { tsa3000c01v1Entry 509 }

		-- 1.3.6.1.4.1.10106.3.101291.1.1.511
		tsa3000c01v1BadCrcPck OBJECT-TYPE
			SYNTAX Uint16
			MAX-ACCESS read-only
			STATUS current
			DESCRIPTION
				"Bad CRC packets"
		::= { tsa3000c01v1Entry 511 }

		-- 1.3.6.1.4.1.10106.3.432201
		tle2001c01v1 OBJECT IDENTIFIER ::= { albalaProducts 432201 }

		-- 1.3.6.1.4.1.10106.3.432201.1
		tle2001c01v1Table  OBJECT-TYPE
			SYNTAX SEQUENCE OF Tle2001c01v1Entry
			MAX-ACCESS not-accessible
			STATUS current
			DESCRIPTION
				"Module  TLE2001C01V1 Table"
			::= { tle2001c01v1 1 }

		-- 1.3.6.1.4.1.10106.3.432201.1.1
		tle2001c01v1Entry  OBJECT-TYPE
			SYNTAX Tle2001c01v1Entry
			MAX-ACCESS not-accessible
			STATUS current
			DESCRIPTION
				"Module TLE2001C01V1 Entry"
			INDEX { tle2001c01v1Index }
			::= { tle2001c01v1Table 1 }

			Tle2001c01v1Entry ::=
			SEQUENCE {
				tle2001c01v1Index
				ModuleIndex,
				tle2001c01v1Gpo1
				Bit0Ina1Act,
				tle2001c01v1Gpo2
				Bit0Ina1Act,
				tle2001c01v1Gpo3
				Bit0Ina1Act,
				tle2001c01v1Gpo4
				Bit0Ina1Act,
				tle2001c01v1InvertGpi1Pol
				Bit0No1Yes,
				tle2001c01v1InvertGpi2Pol
				Bit0No1Yes,
				tle2001c01v1InvertGpi3Pol
				Bit0No1Yes,
				tle2001c01v1InvertGpi4Pol
				Bit0No1Yes,
				tle2001c01v1InvertGpo1Pol
				Bit0No1Yes,
				tle2001c01v1InvertGpo2Pol
				Bit0No1Yes,
				tle2001c01v1InvertGpo3Pol
				Bit0No1Yes,
				tle2001c01v1InvertGpo4Pol
				Bit0No1Yes,
				tle2001c01v1Gpi1
				Bit0Ina1Act,
				tle2001c01v1Gpi1TrapEnable
				AlarmEnable,
				tle2001c01v1Gpi2
				Bit0Ina1Act,
				tle2001c01v1Gpi2TrapEnable
				AlarmEnable,
				tle2001c01v1Gpi3
				Bit0Ina1Act,
				tle2001c01v1Gpi3TrapEnable
				AlarmEnable,
				tle2001c01v1Gpi4
				Bit0Ina1Act,
				tle2001c01v1Gpi4TrapEnable
				AlarmEnable,
				tle2001c01v1RedBoard
				Bit0No1Yes,
				tle2001c01v1RedBoardTrapEnable
				AlarmEnable,
				tle2001c01v1EthLink
				Bit0No1Yes,
				tle2001c01v1EthLinkTrapEnable
				AlarmEnable,
				tle2001c01v1EthRedAct
				Bit0No1Yes,
				tle2001c01v1EthRedActTrapEnable
				AlarmEnable,
				tle2001c01v1App1Ena
				Bit0No1Yes,
				tle2001c01v1App2Ena
				Bit0No1Yes,
				tle2001c01v1App3Ena
				Bit0No1Yes,
				tle2001c01v1App4Ena
				Bit0No1Yes,
				tle2001c01v1App5Ena
				Bit0No1Yes,
				tle2001c01v1App6Ena
				Bit0No1Yes,
				tle2001c01v1App7Ena
				Bit0No1Yes,
				tle2001c01v1App8Ena
				Bit0No1Yes,
				tle2001c01v1App9Ena
				Bit0No1Yes,
				tle2001c01v1App10Ena
				Bit0No1Yes,
				tle2001c01v1App11Ena
				Bit0No1Yes,
				tle2001c01v1App12Ena
				Bit0No1Yes,
				tle2001c01v1App13Ena
				Bit0No1Yes,
				tle2001c01v1App14Ena
				Bit0No1Yes,
				tle2001c01v1App15Ena
				Bit0No1Yes,
				tle2001c01v1App16Ena
				Bit0No1Yes,
				tle2001c01v1SerialNo
				SerialNo
			 }

		-- 1.3.6.1.4.1.10106.3.101291.1.1.1
		tle2001c01v1Index OBJECT-TYPE
			SYNTAX ModuleIndex
			MAX-ACCESS read-only
			STATUS current
			DESCRIPTION
				"Index of TLE2001C01V1 Table"
		::= { tle2001c01v1Entry 1 }

		-- 1.3.6.1.4.1.10106.3.101291.1.1.3
		tle2001c01v1Gpo1 OBJECT-TYPE
			SYNTAX Bit0Ina1Act
			MAX-ACCESS read-write
			STATUS current
			DESCRIPTION
				"Allows control of GPO1"
		::= { tle2001c01v1Entry 3 }

		-- 1.3.6.1.4.1.10106.3.101291.1.1.5
		tle2001c01v1Gpo2 OBJECT-TYPE
			SYNTAX Bit0Ina1Act
			MAX-ACCESS read-write
			STATUS current
			DESCRIPTION
				"Allows control of GPO2"
		::= { tle2001c01v1Entry 5 }

		-- 1.3.6.1.4.1.10106.3.101291.1.1.7
		tle2001c01v1Gpo3 OBJECT-TYPE
			SYNTAX Bit0Ina1Act
			MAX-ACCESS read-write
			STATUS current
			DESCRIPTION
				"Allows control of GPO3"
		::= { tle2001c01v1Entry 7 }

		-- 1.3.6.1.4.1.10106.3.101291.1.1.9
		tle2001c01v1Gpo4 OBJECT-TYPE
			SYNTAX Bit0Ina1Act
			MAX-ACCESS read-write
			STATUS current
			DESCRIPTION
				"Allows control of GPO4"
		::= { tle2001c01v1Entry 9 }

		-- 1.3.6.1.4.1.10106.3.101291.1.1.11
		tle2001c01v1InvertGpi1Pol OBJECT-TYPE
			SYNTAX Bit0No1Yes
			MAX-ACCESS read-write
			STATUS current
			DESCRIPTION
				"Changes GPI1 polarity to normally closed"
		::= { tle2001c01v1Entry 11 }

		-- 1.3.6.1.4.1.10106.3.101291.1.1.13
		tle2001c01v1InvertGpi2Pol OBJECT-TYPE
			SYNTAX Bit0No1Yes
			MAX-ACCESS read-write
			STATUS current
			DESCRIPTION
				"Changes GPI2 polarity to normally closed"
		::= { tle2001c01v1Entry 13 }

		-- 1.3.6.1.4.1.10106.3.101291.1.1.15
		tle2001c01v1InvertGpi3Pol OBJECT-TYPE
			SYNTAX Bit0No1Yes
			MAX-ACCESS read-write
			STATUS current
			DESCRIPTION
				"Changes GPI3 polarity to normally closed"
		::= { tle2001c01v1Entry 15 }

		-- 1.3.6.1.4.1.10106.3.101291.1.1.17
		tle2001c01v1InvertGpi4Pol OBJECT-TYPE
			SYNTAX Bit0No1Yes
			MAX-ACCESS read-write
			STATUS current
			DESCRIPTION
				"Changes GPI4 polarity to normally closed"
		::= { tle2001c01v1Entry 17 }

		-- 1.3.6.1.4.1.10106.3.101291.1.1.19
		tle2001c01v1InvertGpo1Pol OBJECT-TYPE
			SYNTAX Bit0No1Yes
			MAX-ACCESS read-write
			STATUS current
			DESCRIPTION
				"Allows inverting GPO1 polarity"
		::= { tle2001c01v1Entry 19 }

		-- 1.3.6.1.4.1.10106.3.101291.1.1.21
		tle2001c01v1InvertGpo2Pol OBJECT-TYPE
			SYNTAX Bit0No1Yes
			MAX-ACCESS read-write
			STATUS current
			DESCRIPTION
				"Allows inverting GPO2 polarity"
		::= { tle2001c01v1Entry 21 }

		-- 1.3.6.1.4.1.10106.3.101291.1.1.23
		tle2001c01v1InvertGpo3Pol OBJECT-TYPE
			SYNTAX Bit0No1Yes
			MAX-ACCESS read-write
			STATUS current
			DESCRIPTION
				"Allows inverting GPO3 polarity"
		::= { tle2001c01v1Entry 23 }

		-- 1.3.6.1.4.1.10106.3.101291.1.1.25
		tle2001c01v1InvertGpo4Pol OBJECT-TYPE
			SYNTAX Bit0No1Yes
			MAX-ACCESS read-write
			STATUS current
			DESCRIPTION
				"Allows inverting GPO4 polarity"
		::= { tle2001c01v1Entry 25 }

		-- 1.3.6.1.4.1.10106.3.101291.1.1.27
		tle2001c01v1Gpi1 OBJECT-TYPE
			SYNTAX Bit0Ina1Act
			MAX-ACCESS read-only
			STATUS current
			DESCRIPTION
				"GPI1 status"
		::= { tle2001c01v1Entry 27 }

		-- 1.3.6.1.4.1.10106.3.101291.1.1.28
		tle2001c01v1Gpi1TrapEnable OBJECT-TYPE
			SYNTAX AlarmEnable
			MAX-ACCESS read-write
			STATUS current
			DESCRIPTION
				"GPI1 status Trap Enable"
		::= { tle2001c01v1Entry 28 }

		-- 1.3.6.1.4.1.10106.3.101291.1.1.29
		tle2001c01v1Gpi2 OBJECT-TYPE
			SYNTAX Bit0Ina1Act
			MAX-ACCESS read-only
			STATUS current
			DESCRIPTION
				"GPI2 status"
		::= { tle2001c01v1Entry 29 }

		-- 1.3.6.1.4.1.10106.3.101291.1.1.30
		tle2001c01v1Gpi2TrapEnable OBJECT-TYPE
			SYNTAX AlarmEnable
			MAX-ACCESS read-write
			STATUS current
			DESCRIPTION
				"GPI2 status Trap Enable"
		::= { tle2001c01v1Entry 30 }

		-- 1.3.6.1.4.1.10106.3.101291.1.1.31
		tle2001c01v1Gpi3 OBJECT-TYPE
			SYNTAX Bit0Ina1Act
			MAX-ACCESS read-only
			STATUS current
			DESCRIPTION
				"GPI3 status"
		::= { tle2001c01v1Entry 31 }

		-- 1.3.6.1.4.1.10106.3.101291.1.1.32
		tle2001c01v1Gpi3TrapEnable OBJECT-TYPE
			SYNTAX AlarmEnable
			MAX-ACCESS read-write
			STATUS current
			DESCRIPTION
				"GPI3 status Trap Enable"
		::= { tle2001c01v1Entry 32 }

		-- 1.3.6.1.4.1.10106.3.101291.1.1.33
		tle2001c01v1Gpi4 OBJECT-TYPE
			SYNTAX Bit0Ina1Act
			MAX-ACCESS read-only
			STATUS current
			DESCRIPTION
				"GPI4 status"
		::= { tle2001c01v1Entry 33 }

		-- 1.3.6.1.4.1.10106.3.101291.1.1.34
		tle2001c01v1Gpi4TrapEnable OBJECT-TYPE
			SYNTAX AlarmEnable
			MAX-ACCESS read-write
			STATUS current
			DESCRIPTION
				"GPI4 status Trap Enable"
		::= { tle2001c01v1Entry 34 }

		-- 1.3.6.1.4.1.10106.3.101291.1.1.35
		tle2001c01v1RedBoard OBJECT-TYPE
			SYNTAX Bit0No1Yes
			MAX-ACCESS read-only
			STATUS current
			DESCRIPTION
				"Indicates that there are two modules in redundant configuration"
		::= { tle2001c01v1Entry 35 }

		-- 1.3.6.1.4.1.10106.3.101291.1.1.36
		tle2001c01v1RedBoardTrapEnable OBJECT-TYPE
			SYNTAX AlarmEnable
			MAX-ACCESS read-write
			STATUS current
			DESCRIPTION
				"Indicates that there are two modules in redundant configuration Trap Enable"
		::= { tle2001c01v1Entry 36 }

		-- 1.3.6.1.4.1.10106.3.101291.1.1.37
		tle2001c01v1EthLink OBJECT-TYPE
			SYNTAX Bit0No1Yes
			MAX-ACCESS read-only
			STATUS current
			DESCRIPTION
				"Indicates that the Ethernet link is OK"
		::= { tle2001c01v1Entry 37 }

		-- 1.3.6.1.4.1.10106.3.101291.1.1.38
		tle2001c01v1EthLinkTrapEnable OBJECT-TYPE
			SYNTAX AlarmEnable
			MAX-ACCESS read-write
			STATUS current
			DESCRIPTION
				"Indicates that the Ethernet link is OK Trap Enable"
		::= { tle2001c01v1Entry 38 }

		-- 1.3.6.1.4.1.10106.3.101291.1.1.39
		tle2001c01v1EthRedAct OBJECT-TYPE
			SYNTAX Bit0No1Yes
			MAX-ACCESS read-only
			STATUS current
			DESCRIPTION
				"Indicates that this is the active module of the redundant configuration"
		::= { tle2001c01v1Entry 39 }

		-- 1.3.6.1.4.1.10106.3.101291.1.1.40
		tle2001c01v1EthRedActTrapEnable OBJECT-TYPE
			SYNTAX AlarmEnable
			MAX-ACCESS read-write
			STATUS current
			DESCRIPTION
				"Indicates that this is the active module of the redundant configuration Trap Enable"
		::= { tle2001c01v1Entry 40 }

		-- 1.3.6.1.4.1.10106.3.101291.1.1.41
		tle2001c01v1App1Ena OBJECT-TYPE
			SYNTAX Bit0No1Yes
			MAX-ACCESS read-only
			STATUS current
			DESCRIPTION
				"Indicates the event log is enabled"
		::= { tle2001c01v1Entry 41 }

		-- 1.3.6.1.4.1.10106.3.101291.1.1.43
		tle2001c01v1App2Ena OBJECT-TYPE
			SYNTAX Bit0No1Yes
			MAX-ACCESS read-only
			STATUS current
			DESCRIPTION
				"Indicates the SNMP is enabled"
		::= { tle2001c01v1Entry 43 }

		-- 1.3.6.1.4.1.10106.3.101291.1.1.45
		tle2001c01v1App3Ena OBJECT-TYPE
			SYNTAX Bit0No1Yes
			MAX-ACCESS read-only
			STATUS current
			DESCRIPTION
				"Indicates the access control is enabled"
		::= { tle2001c01v1Entry 45 }

		-- 1.3.6.1.4.1.10106.3.101291.1.1.47
		tle2001c01v1App4Ena OBJECT-TYPE
			SYNTAX Bit0No1Yes
			MAX-ACCESS read-only
			STATUS current
			DESCRIPTION
				"Indicates the application 4 is enabled"
		::= { tle2001c01v1Entry 47 }

		-- 1.3.6.1.4.1.10106.3.101291.1.1.49
		tle2001c01v1App5Ena OBJECT-TYPE
			SYNTAX Bit0No1Yes
			MAX-ACCESS read-only
			STATUS current
			DESCRIPTION
				"Indicates the application 5 is enabled"
		::= { tle2001c01v1Entry 49 }

		-- 1.3.6.1.4.1.10106.3.101291.1.1.51
		tle2001c01v1App6Ena OBJECT-TYPE
			SYNTAX Bit0No1Yes
			MAX-ACCESS read-only
			STATUS current
			DESCRIPTION
				"Indicates the application 6 is enabled"
		::= { tle2001c01v1Entry 51 }

		-- 1.3.6.1.4.1.10106.3.101291.1.1.53
		tle2001c01v1App7Ena OBJECT-TYPE
			SYNTAX Bit0No1Yes
			MAX-ACCESS read-only
			STATUS current
			DESCRIPTION
				"Indicates the application 7 is enabled"
		::= { tle2001c01v1Entry 53 }

		-- 1.3.6.1.4.1.10106.3.101291.1.1.55
		tle2001c01v1App8Ena OBJECT-TYPE
			SYNTAX Bit0No1Yes
			MAX-ACCESS read-only
			STATUS current
			DESCRIPTION
				"Indicates the application 8 is enabled"
		::= { tle2001c01v1Entry 55 }

		-- 1.3.6.1.4.1.10106.3.101291.1.1.57
		tle2001c01v1App9Ena OBJECT-TYPE
			SYNTAX Bit0No1Yes
			MAX-ACCESS read-only
			STATUS current
			DESCRIPTION
				"Indicates the application 9 is enabled"
		::= { tle2001c01v1Entry 57 }

		-- 1.3.6.1.4.1.10106.3.101291.1.1.59
		tle2001c01v1App10Ena OBJECT-TYPE
			SYNTAX Bit0No1Yes
			MAX-ACCESS read-only
			STATUS current
			DESCRIPTION
				"Indicates the application 10 is enabled"
		::= { tle2001c01v1Entry 59 }

		-- 1.3.6.1.4.1.10106.3.101291.1.1.61
		tle2001c01v1App11Ena OBJECT-TYPE
			SYNTAX Bit0No1Yes
			MAX-ACCESS read-only
			STATUS current
			DESCRIPTION
				"Indicates the application 11 is enabled"
		::= { tle2001c01v1Entry 61 }

		-- 1.3.6.1.4.1.10106.3.101291.1.1.63
		tle2001c01v1App12Ena OBJECT-TYPE
			SYNTAX Bit0No1Yes
			MAX-ACCESS read-only
			STATUS current
			DESCRIPTION
				"Indicates the application 12 is enabled"
		::= { tle2001c01v1Entry 63 }

		-- 1.3.6.1.4.1.10106.3.101291.1.1.65
		tle2001c01v1App13Ena OBJECT-TYPE
			SYNTAX Bit0No1Yes
			MAX-ACCESS read-only
			STATUS current
			DESCRIPTION
				"Indicates the application 13 is enabled"
		::= { tle2001c01v1Entry 65 }

		-- 1.3.6.1.4.1.10106.3.101291.1.1.67
		tle2001c01v1App14Ena OBJECT-TYPE
			SYNTAX Bit0No1Yes
			MAX-ACCESS read-only
			STATUS current
			DESCRIPTION
				"Indicates the application 14 is enabled"
		::= { tle2001c01v1Entry 67 }

		-- 1.3.6.1.4.1.10106.3.101291.1.1.69
		tle2001c01v1App15Ena OBJECT-TYPE
			SYNTAX Bit0No1Yes
			MAX-ACCESS read-only
			STATUS current
			DESCRIPTION
				"Indicates the application 15 is enabled"
		::= { tle2001c01v1Entry 69 }

		-- 1.3.6.1.4.1.10106.3.101291.1.1.71
		tle2001c01v1App16Ena OBJECT-TYPE
			SYNTAX Bit0No1Yes
			MAX-ACCESS read-only
			STATUS current
			DESCRIPTION
				"Indicates the application 16 is enabled"
		::= { tle2001c01v1Entry 71 }

		-- 1.3.6.1.4.1.10106.3.101291.1.1.73
		tle2001c01v1SerialNo OBJECT-TYPE
			SYNTAX SerialNo
			MAX-ACCESS read-only
			STATUS current
			DESCRIPTION
				"Serial number"
		::= { tle2001c01v1Entry 73 }

		-- 1.3.6.1.4.1.10106.3.436601
		psu2000c02v1 OBJECT IDENTIFIER ::= { albalaProducts 436601 }

		-- 1.3.6.1.4.1.10106.3.436601.1
		psu2000c02v1Table  OBJECT-TYPE
			SYNTAX SEQUENCE OF Psu2000c02v1Entry
			MAX-ACCESS not-accessible
			STATUS current
			DESCRIPTION
				"Module  PSU2000C02V1 Table"
			::= { psu2000c02v1 1 }

		-- 1.3.6.1.4.1.10106.3.436601.1.1
		psu2000c02v1Entry  OBJECT-TYPE
			SYNTAX Psu2000c02v1Entry
			MAX-ACCESS not-accessible
			STATUS current
			DESCRIPTION
				"Module PSU2000C02V1 Entry"
			INDEX { psu2000c02v1Index }
			::= { psu2000c02v1Table 1 }

			Psu2000c02v1Entry ::=
			SEQUENCE {
				psu2000c02v1Index
				ModuleIndex,
				psu2000c02v1PowerOff
				BitFail,
				psu2000c02v1PowerOffTrapEnable
				AlarmEnable,
				psu2000c02v1TempWarning
				BitFail,
				psu2000c02v1TempWarningTrapEnable
				AlarmEnable,
				psu2000c02v1TempFail
				BitFail,
				psu2000c02v1TempFailTrapEnable
				AlarmEnable,
				psu2000c02v1ActTemp
				Temperature0c1,
				psu2000c02v1MeanTemp
				Temperature0c1,
				psu2000c02v1MaxTemp
				Temperature0c1,
				psu2000c02v1PonHours
				TimeX1Hour,
				psu2000c02v1TotMaxTemp
				Temperature0c1,
				psu2000c02v1TotPonHours
				TimeX1Hour,
				psu2000c02v1TotPonTimes
				Uint16,
				psu2000c02v1SerialNo
				SerialNo
			 }

		-- 1.3.6.1.4.1.10106.3.101291.1.1.1
		psu2000c02v1Index OBJECT-TYPE
			SYNTAX ModuleIndex
			MAX-ACCESS read-only
			STATUS current
			DESCRIPTION
				"Index of PSU2000C02V1 Table"
		::= { psu2000c02v1Entry 1 }

		-- 1.3.6.1.4.1.10106.3.101291.1.1.3
		psu2000c02v1PowerOff OBJECT-TYPE
			SYNTAX BitFail
			MAX-ACCESS read-only
			STATUS current
			DESCRIPTION
				"Indicates the power supply status"
		::= { psu2000c02v1Entry 3 }

		-- 1.3.6.1.4.1.10106.3.101291.1.1.4
		psu2000c02v1PowerOffTrapEnable OBJECT-TYPE
			SYNTAX AlarmEnable
			MAX-ACCESS read-write
			STATUS current
			DESCRIPTION
				"Indicates the power supply status Trap Enable"
		::= { psu2000c02v1Entry 4 }

		-- 1.3.6.1.4.1.10106.3.101291.1.1.5
		psu2000c02v1TempWarning OBJECT-TYPE
			SYNTAX BitFail
			MAX-ACCESS read-only
			STATUS current
			DESCRIPTION
				"Indicates that actual temperature is over expected range"
		::= { psu2000c02v1Entry 5 }

		-- 1.3.6.1.4.1.10106.3.101291.1.1.6
		psu2000c02v1TempWarningTrapEnable OBJECT-TYPE
			SYNTAX AlarmEnable
			MAX-ACCESS read-write
			STATUS current
			DESCRIPTION
				"Indicates that actual temperature is over expected range Trap Enable"
		::= { psu2000c02v1Entry 6 }

		-- 1.3.6.1.4.1.10106.3.101291.1.1.7
		psu2000c02v1TempFail OBJECT-TYPE
			SYNTAX BitFail
			MAX-ACCESS read-only
			STATUS current
			DESCRIPTION
				"Indicates that actual temperature is over recommended range"
		::= { psu2000c02v1Entry 7 }

		-- 1.3.6.1.4.1.10106.3.101291.1.1.8
		psu2000c02v1TempFailTrapEnable OBJECT-TYPE
			SYNTAX AlarmEnable
			MAX-ACCESS read-write
			STATUS current
			DESCRIPTION
				"Indicates that actual temperature is over recommended range Trap Enable"
		::= { psu2000c02v1Entry 8 }

		-- 1.3.6.1.4.1.10106.3.101291.1.1.9
		psu2000c02v1ActTemp OBJECT-TYPE
			SYNTAX Temperature0c1
			MAX-ACCESS read-only
			STATUS current
			DESCRIPTION
				"Displays internal actual temperature"
		::= { psu2000c02v1Entry 9 }

		-- 1.3.6.1.4.1.10106.3.101291.1.1.11
		psu2000c02v1MeanTemp OBJECT-TYPE
			SYNTAX Temperature0c1
			MAX-ACCESS read-only
			STATUS current
			DESCRIPTION
				"Displays internal mean temperature"
		::= { psu2000c02v1Entry 11 }

		-- 1.3.6.1.4.1.10106.3.101291.1.1.13
		psu2000c02v1MaxTemp OBJECT-TYPE
			SYNTAX Temperature0c1
			MAX-ACCESS read-only
			STATUS current
			DESCRIPTION
				"Displays internal maximun temperature"
		::= { psu2000c02v1Entry 13 }

		-- 1.3.6.1.4.1.10106.3.101291.1.1.15
		psu2000c02v1PonHours OBJECT-TYPE
			SYNTAX TimeX1Hour
			MAX-ACCESS read-only
			STATUS current
			DESCRIPTION
				"Displays module power on time"
		::= { psu2000c02v1Entry 15 }

		-- 1.3.6.1.4.1.10106.3.101291.1.1.17
		psu2000c02v1TotMaxTemp OBJECT-TYPE
			SYNTAX Temperature0c1
			MAX-ACCESS read-only
			STATUS current
			DESCRIPTION
				"Displays internal maximun tempertature since first power on"
		::= { psu2000c02v1Entry 17 }

		-- 1.3.6.1.4.1.10106.3.101291.1.1.19
		psu2000c02v1TotPonHours OBJECT-TYPE
			SYNTAX TimeX1Hour
			MAX-ACCESS read-only
			STATUS current
			DESCRIPTION
				"Displays module power on time since first power on"
		::= { psu2000c02v1Entry 19 }

		-- 1.3.6.1.4.1.10106.3.101291.1.1.21
		psu2000c02v1TotPonTimes OBJECT-TYPE
			SYNTAX Uint16
			MAX-ACCESS read-only
			STATUS current
			DESCRIPTION
				"Displays module power on events since first power on"
		::= { psu2000c02v1Entry 21 }

		-- 1.3.6.1.4.1.10106.3.101291.1.1.23
		psu2000c02v1SerialNo OBJECT-TYPE
			SYNTAX SerialNo
			MAX-ACCESS read-only
			STATUS current
			DESCRIPTION
				"Serial number"
		::= { psu2000c02v1Entry 23 }

		-- 1.3.6.1.4.1.10106.3.437801
		eop2000c01v1 OBJECT IDENTIFIER ::= { albalaProducts 437801 }

		-- 1.3.6.1.4.1.10106.3.437801.1
		eop2000c01v1Table  OBJECT-TYPE
			SYNTAX SEQUENCE OF Eop2000c01v1Entry
			MAX-ACCESS not-accessible
			STATUS current
			DESCRIPTION
				"Module  EOP2000C01V1 Table"
			::= { eop2000c01v1 1 }

		-- 1.3.6.1.4.1.10106.3.437801.1.1
		eop2000c01v1Entry  OBJECT-TYPE
			SYNTAX Eop2000c01v1Entry
			MAX-ACCESS not-accessible
			STATUS current
			DESCRIPTION
				"Module EOP2000C01V1 Entry"
			INDEX { eop2000c01v1Index }
			::= { eop2000c01v1Table 1 }

			Eop2000c01v1Entry ::=
			SEQUENCE {
				eop2000c01v1Index
				ModuleIndex,
				eop2000c01v1InputA
				EopInput,
				eop2000c01v1InputATrapEnable
				AlarmEnable,
				eop2000c01v1InputB
				EopInput,
				eop2000c01v1InputBTrapEnable
				AlarmEnable,
				eop2000c01v1Mode
				Bit0Aut1Man,
				eop2000c01v1BckTxEn
				Bit0Dis1Ena,
				eop2000c01v1UnlockA
				BitFail,
				eop2000c01v1UnlockATrapEnable
				AlarmEnable,
				eop2000c01v1LFailA
				BitFail,
				eop2000c01v1LFailATrapEnable
				AlarmEnable,
				eop2000c01v1HdA
				Bit0Sd1Hd,
				eop2000c01v1NoElecA
				BitFail,
				eop2000c01v1NoOpticA
				BitFail,
				eop2000c01v1UnlockB
				BitFail,
				eop2000c01v1UnlockBTrapEnable
				AlarmEnable,
				eop2000c01v1LFailB
				BitFail,
				eop2000c01v1LFailBTrapEnable
				AlarmEnable,
				eop2000c01v1HdB
				Bit0Sd1Hd,
				eop2000c01v1NoElecB
				BitFail,
				eop2000c01v1NoOpticB
				BitFail,
				eop2000c01v1OpTxPres
				Bit0No1Yes,
				eop2000c01v1OpTxPresTrapEnable
				AlarmEnable,
				eop2000c01v1OpRxPres
				Bit0No1Yes,
				eop2000c01v1OpRxPresTrapEnable
				AlarmEnable,
				eop2000c01v1SfpTxSn
				SerialNo,
				eop2000c01v1SfpRxSn
				SerialNo,
				eop2000c01v1SerialNo
				SerialNo,
				eop2000c01v1RxPowerA
				OptPowerX2Uw,
				eop2000c01v1RxPowerB
				OptPowerX2Uw,
				eop2000c01v1WavelengthA
				Wavelength1,
				eop2000c01v1WavelengthB
				Wavelength1
			 }

		-- 1.3.6.1.4.1.10106.3.101291.1.1.1
		eop2000c01v1Index OBJECT-TYPE
			SYNTAX ModuleIndex
			MAX-ACCESS read-only
			STATUS current
			DESCRIPTION
				"Index of EOP2000C01V1 Table"
		::= { eop2000c01v1Entry 1 }

		-- 1.3.6.1.4.1.10106.3.101291.1.1.3
		eop2000c01v1InputA OBJECT-TYPE
			SYNTAX EopInput
			MAX-ACCESS read-write
			STATUS current
			DESCRIPTION
				"Indicates the input selected"
		::= { eop2000c01v1Entry 3 }

		-- 1.3.6.1.4.1.10106.3.101291.1.1.4
		eop2000c01v1InputATrapEnable OBJECT-TYPE
			SYNTAX AlarmEnable
			MAX-ACCESS read-write
			STATUS current
			DESCRIPTION
				"Indicates the input selected Trap Enable"
		::= { eop2000c01v1Entry 4 }

		-- 1.3.6.1.4.1.10106.3.101291.1.1.5
		eop2000c01v1InputB OBJECT-TYPE
			SYNTAX EopInput
			MAX-ACCESS read-write
			STATUS current
			DESCRIPTION
				"Indicates the input selected"
		::= { eop2000c01v1Entry 5 }

		-- 1.3.6.1.4.1.10106.3.101291.1.1.6
		eop2000c01v1InputBTrapEnable OBJECT-TYPE
			SYNTAX AlarmEnable
			MAX-ACCESS read-write
			STATUS current
			DESCRIPTION
				"Indicates the input selected Trap Enable"
		::= { eop2000c01v1Entry 6 }

		-- 1.3.6.1.4.1.10106.3.101291.1.1.7
		eop2000c01v1Mode OBJECT-TYPE
			SYNTAX Bit0Aut1Man
			MAX-ACCESS read-write
			STATUS current
			DESCRIPTION
				"Operating mode"
		::= { eop2000c01v1Entry 7 }

		-- 1.3.6.1.4.1.10106.3.101291.1.1.9
		eop2000c01v1BckTxEn OBJECT-TYPE
			SYNTAX Bit0Dis1Ena
			MAX-ACCESS read-write
			STATUS current
			DESCRIPTION
				"Enables the drivers that transmit to backplane"
		::= { eop2000c01v1Entry 9 }

		-- 1.3.6.1.4.1.10106.3.101291.1.1.11
		eop2000c01v1UnlockA OBJECT-TYPE
			SYNTAX BitFail
			MAX-ACCESS read-only
			STATUS current
			DESCRIPTION
				"Indicates signal unlock fail"
		::= { eop2000c01v1Entry 11 }

		-- 1.3.6.1.4.1.10106.3.101291.1.1.12
		eop2000c01v1UnlockATrapEnable OBJECT-TYPE
			SYNTAX AlarmEnable
			MAX-ACCESS read-write
			STATUS current
			DESCRIPTION
				"Indicates signal unlock fail Trap Enable"
		::= { eop2000c01v1Entry 12 }

		-- 1.3.6.1.4.1.10106.3.101291.1.1.13
		eop2000c01v1LFailA OBJECT-TYPE
			SYNTAX BitFail
			MAX-ACCESS read-only
			STATUS current
			DESCRIPTION
				"Indicates a fail in laser"
		::= { eop2000c01v1Entry 13 }

		-- 1.3.6.1.4.1.10106.3.101291.1.1.14
		eop2000c01v1LFailATrapEnable OBJECT-TYPE
			SYNTAX AlarmEnable
			MAX-ACCESS read-write
			STATUS current
			DESCRIPTION
				"Indicates a fail in laser Trap Enable"
		::= { eop2000c01v1Entry 14 }

		-- 1.3.6.1.4.1.10106.3.101291.1.1.15
		eop2000c01v1HdA OBJECT-TYPE
			SYNTAX Bit0Sd1Hd
			MAX-ACCESS read-only
			STATUS current
			DESCRIPTION
				"Indicates the SDI signal type"
		::= { eop2000c01v1Entry 15 }

		-- 1.3.6.1.4.1.10106.3.101291.1.1.17
		eop2000c01v1NoElecA OBJECT-TYPE
			SYNTAX BitFail
			MAX-ACCESS read-only
			STATUS current
			DESCRIPTION
				"Electrical input signal status"
		::= { eop2000c01v1Entry 17 }

		-- 1.3.6.1.4.1.10106.3.101291.1.1.19
		eop2000c01v1NoOpticA OBJECT-TYPE
			SYNTAX BitFail
			MAX-ACCESS read-only
			STATUS current
			DESCRIPTION
				"Optical input signal status"
		::= { eop2000c01v1Entry 19 }

		-- 1.3.6.1.4.1.10106.3.101291.1.1.21
		eop2000c01v1UnlockB OBJECT-TYPE
			SYNTAX BitFail
			MAX-ACCESS read-only
			STATUS current
			DESCRIPTION
				"Indicates signal unlock fail"
		::= { eop2000c01v1Entry 21 }

		-- 1.3.6.1.4.1.10106.3.101291.1.1.22
		eop2000c01v1UnlockBTrapEnable OBJECT-TYPE
			SYNTAX AlarmEnable
			MAX-ACCESS read-write
			STATUS current
			DESCRIPTION
				"Indicates signal unlock fail Trap Enable"
		::= { eop2000c01v1Entry 22 }

		-- 1.3.6.1.4.1.10106.3.101291.1.1.23
		eop2000c01v1LFailB OBJECT-TYPE
			SYNTAX BitFail
			MAX-ACCESS read-only
			STATUS current
			DESCRIPTION
				"Indicates a fail in laser"
		::= { eop2000c01v1Entry 23 }

		-- 1.3.6.1.4.1.10106.3.101291.1.1.24
		eop2000c01v1LFailBTrapEnable OBJECT-TYPE
			SYNTAX AlarmEnable
			MAX-ACCESS read-write
			STATUS current
			DESCRIPTION
				"Indicates a fail in laser Trap Enable"
		::= { eop2000c01v1Entry 24 }

		-- 1.3.6.1.4.1.10106.3.101291.1.1.25
		eop2000c01v1HdB OBJECT-TYPE
			SYNTAX Bit0Sd1Hd
			MAX-ACCESS read-only
			STATUS current
			DESCRIPTION
				"Indicates the SDI signal type"
		::= { eop2000c01v1Entry 25 }

		-- 1.3.6.1.4.1.10106.3.101291.1.1.27
		eop2000c01v1NoElecB OBJECT-TYPE
			SYNTAX BitFail
			MAX-ACCESS read-only
			STATUS current
			DESCRIPTION
				"Electrical input signal status"
		::= { eop2000c01v1Entry 27 }

		-- 1.3.6.1.4.1.10106.3.101291.1.1.29
		eop2000c01v1NoOpticB OBJECT-TYPE
			SYNTAX BitFail
			MAX-ACCESS read-only
			STATUS current
			DESCRIPTION
				"Optical input signal status"
		::= { eop2000c01v1Entry 29 }

		-- 1.3.6.1.4.1.10106.3.101291.1.1.31
		eop2000c01v1OpTxPres OBJECT-TYPE
			SYNTAX Bit0No1Yes
			MAX-ACCESS read-only
			STATUS current
			DESCRIPTION
				"Indicates the presence of a SFP TX module"
		::= { eop2000c01v1Entry 31 }

		-- 1.3.6.1.4.1.10106.3.101291.1.1.32
		eop2000c01v1OpTxPresTrapEnable OBJECT-TYPE
			SYNTAX AlarmEnable
			MAX-ACCESS read-write
			STATUS current
			DESCRIPTION
				"Indicates the presence of a SFP TX module Trap Enable"
		::= { eop2000c01v1Entry 32 }

		-- 1.3.6.1.4.1.10106.3.101291.1.1.33
		eop2000c01v1OpRxPres OBJECT-TYPE
			SYNTAX Bit0No1Yes
			MAX-ACCESS read-only
			STATUS current
			DESCRIPTION
				"Indicates the presence of a SFP RX module"
		::= { eop2000c01v1Entry 33 }

		-- 1.3.6.1.4.1.10106.3.101291.1.1.34
		eop2000c01v1OpRxPresTrapEnable OBJECT-TYPE
			SYNTAX AlarmEnable
			MAX-ACCESS read-write
			STATUS current
			DESCRIPTION
				"Indicates the presence of a SFP RX module Trap Enable"
		::= { eop2000c01v1Entry 34 }

		-- 1.3.6.1.4.1.10106.3.101291.1.1.35
		eop2000c01v1SfpTxSn OBJECT-TYPE
			SYNTAX SerialNo
			MAX-ACCESS read-only
			STATUS current
			DESCRIPTION
				"SFP TX Serial number"
		::= { eop2000c01v1Entry 35 }

		-- 1.3.6.1.4.1.10106.3.101291.1.1.37
		eop2000c01v1SfpRxSn OBJECT-TYPE
			SYNTAX SerialNo
			MAX-ACCESS read-only
			STATUS current
			DESCRIPTION
				"SFP RX Serial number"
		::= { eop2000c01v1Entry 37 }

		-- 1.3.6.1.4.1.10106.3.101291.1.1.39
		eop2000c01v1SerialNo OBJECT-TYPE
			SYNTAX SerialNo
			MAX-ACCESS read-only
			STATUS current
			DESCRIPTION
				"Serial number"
		::= { eop2000c01v1Entry 39 }

		-- 1.3.6.1.4.1.10106.3.101291.1.1.41
		eop2000c01v1RxPowerA OBJECT-TYPE
			SYNTAX OptPowerX2Uw
			MAX-ACCESS read-only
			STATUS current
			DESCRIPTION
				"Optical received power"
		::= { eop2000c01v1Entry 41 }

		-- 1.3.6.1.4.1.10106.3.101291.1.1.43
		eop2000c01v1RxPowerB OBJECT-TYPE
			SYNTAX OptPowerX2Uw
			MAX-ACCESS read-only
			STATUS current
			DESCRIPTION
				"Optical received power"
		::= { eop2000c01v1Entry 43 }

		-- 1.3.6.1.4.1.10106.3.101291.1.1.45
		eop2000c01v1WavelengthA OBJECT-TYPE
			SYNTAX Wavelength1
			MAX-ACCESS read-only
			STATUS current
			DESCRIPTION
				"Laser wavelength"
		::= { eop2000c01v1Entry 45 }

		-- 1.3.6.1.4.1.10106.3.101291.1.1.47
		eop2000c01v1WavelengthB OBJECT-TYPE
			SYNTAX Wavelength1
			MAX-ACCESS read-only
			STATUS current
			DESCRIPTION
				"Laser wavelength"
		::= { eop2000c01v1Entry 47 }

		-- 1.3.6.1.4.1.10106.3.438701
		avd2001c01v1 OBJECT IDENTIFIER ::= { albalaProducts 438701 }

		-- 1.3.6.1.4.1.10106.3.438701.1
		avd2001c01v1Table  OBJECT-TYPE
			SYNTAX SEQUENCE OF Avd2001c01v1Entry
			MAX-ACCESS not-accessible
			STATUS current
			DESCRIPTION
				"Module  AVD2001C01V1 Table"
			::= { avd2001c01v1 1 }

		-- 1.3.6.1.4.1.10106.3.438701.1.1
		avd2001c01v1Entry  OBJECT-TYPE
			SYNTAX Avd2001c01v1Entry
			MAX-ACCESS not-accessible
			STATUS current
			DESCRIPTION
				"Module AVD2001C01V1 Entry"
			INDEX { avd2001c01v1Index }
			::= { avd2001c01v1Table 1 }

			Avd2001c01v1Entry ::=
			SEQUENCE {
				avd2001c01v1Index
				ModuleIndex,
				avd2001c01v1ClampEnable
				Bit0No1Yes,
				avd2001c01v1ClampMode
				Bit0No1Yes,
				avd2001c01v1LoopEnable
				Bit0No1Yes,
				avd2001c01v1NoSigA
				BitFail,
				avd2001c01v1NoSigATrapEnable
				AlarmEnable,
				avd2001c01v1UnlockA
				BitFail,
				avd2001c01v1UnlockATrapEnable
				AlarmEnable,
				avd2001c01v1SyncFormat
				SdiHd3gFmt3,
				avd2001c01v1SyncFormatTrapEnable
				AlarmEnable,
				avd2001c01v1SerialNo
				SerialNo
			 }

		-- 1.3.6.1.4.1.10106.3.101291.1.1.1
		avd2001c01v1Index OBJECT-TYPE
			SYNTAX ModuleIndex
			MAX-ACCESS read-only
			STATUS current
			DESCRIPTION
				"Index of AVD2001C01V1 Table"
		::= { avd2001c01v1Entry 1 }

		-- 1.3.6.1.4.1.10106.3.101291.1.1.3
		avd2001c01v1ClampEnable OBJECT-TYPE
			SYNTAX Bit0No1Yes
			MAX-ACCESS read-write
			STATUS current
			DESCRIPTION
				"Allows enabling clamping"
		::= { avd2001c01v1Entry 3 }

		-- 1.3.6.1.4.1.10106.3.101291.1.1.5
		avd2001c01v1ClampMode OBJECT-TYPE
			SYNTAX Bit0No1Yes
			MAX-ACCESS read-write
			STATUS current
			DESCRIPTION
				"Allows selecting soft clamping"
		::= { avd2001c01v1Entry 5 }

		-- 1.3.6.1.4.1.10106.3.101291.1.1.7
		avd2001c01v1LoopEnable OBJECT-TYPE
			SYNTAX Bit0No1Yes
			MAX-ACCESS read-write
			STATUS current
			DESCRIPTION
				"Allows enabling loop input"
		::= { avd2001c01v1Entry 7 }

		-- 1.3.6.1.4.1.10106.3.101291.1.1.9
		avd2001c01v1NoSigA OBJECT-TYPE
			SYNTAX BitFail
			MAX-ACCESS read-only
			STATUS current
			DESCRIPTION
				"Input signal status"
		::= { avd2001c01v1Entry 9 }

		-- 1.3.6.1.4.1.10106.3.101291.1.1.10
		avd2001c01v1NoSigATrapEnable OBJECT-TYPE
			SYNTAX AlarmEnable
			MAX-ACCESS read-write
			STATUS current
			DESCRIPTION
				"Input signal status Trap Enable"
		::= { avd2001c01v1Entry 10 }

		-- 1.3.6.1.4.1.10106.3.101291.1.1.11
		avd2001c01v1UnlockA OBJECT-TYPE
			SYNTAX BitFail
			MAX-ACCESS read-only
			STATUS current
			DESCRIPTION
				"Indicates signal unlock fail"
		::= { avd2001c01v1Entry 11 }

		-- 1.3.6.1.4.1.10106.3.101291.1.1.12
		avd2001c01v1UnlockATrapEnable OBJECT-TYPE
			SYNTAX AlarmEnable
			MAX-ACCESS read-write
			STATUS current
			DESCRIPTION
				"Indicates signal unlock fail Trap Enable"
		::= { avd2001c01v1Entry 12 }

		-- 1.3.6.1.4.1.10106.3.101291.1.1.13
		avd2001c01v1SyncFormat OBJECT-TYPE
			SYNTAX SdiHd3gFmt3
			MAX-ACCESS read-only
			STATUS current
			DESCRIPTION
				"Displays signal's  input format"
		::= { avd2001c01v1Entry 13 }

		-- 1.3.6.1.4.1.10106.3.101291.1.1.14
		avd2001c01v1SyncFormatTrapEnable OBJECT-TYPE
			SYNTAX AlarmEnable
			MAX-ACCESS read-write
			STATUS current
			DESCRIPTION
				"Displays signal's  input format Trap Enable"
		::= { avd2001c01v1Entry 14 }

		-- 1.3.6.1.4.1.10106.3.101291.1.1.15
		avd2001c01v1SerialNo OBJECT-TYPE
			SYNTAX SerialNo
			MAX-ACCESS read-only
			STATUS current
			DESCRIPTION
				"Serial number"
		::= { avd2001c01v1Entry 15 }

		-- 1.3.6.1.4.1.10106.3.442301
		hdc2000c01v1 OBJECT IDENTIFIER ::= { albalaProducts 442301 }

		-- 1.3.6.1.4.1.10106.3.442301.1
		hdc2000c01v1Table  OBJECT-TYPE
			SYNTAX SEQUENCE OF Hdc2000c01v1Entry
			MAX-ACCESS not-accessible
			STATUS current
			DESCRIPTION
				"Module  HDC2000C01V1 Table"
			::= { hdc2000c01v1 1 }

		-- 1.3.6.1.4.1.10106.3.442301.1.1
		hdc2000c01v1Entry  OBJECT-TYPE
			SYNTAX Hdc2000c01v1Entry
			MAX-ACCESS not-accessible
			STATUS current
			DESCRIPTION
				"Module HDC2000C01V1 Entry"
			INDEX { hdc2000c01v1Index }
			::= { hdc2000c01v1Table 1 }

			Hdc2000c01v1Entry ::=
			SEQUENCE {
				hdc2000c01v1Index
				ModuleIndex,
				hdc2000c01v1ActivePreset
				Preset16Active,
				hdc2000c01v1LoadPreset
				Preset16Load,
				hdc2000c01v1SavePreset
				Preset16Save,
				hdc2000c01v1AnaRefFmt
				SdiHd3gFmt5,
				hdc2000c01v1AnaRefFmtTrapEnable
				AlarmEnable,
				hdc2000c01v1GenlockMode
				GenlockM0de2,
				hdc2000c01v1EnaAud20Bit
				Bit0No1Yes,
				hdc2000c01v1ModeConv
				Bit0Aut1Man,
				hdc2000c01v1ModeConvTrapEnable
				AlarmEnable,
				hdc2000c01v1OutAfd
				Afd1,
				hdc2000c01v1OutAfdTrapEnable
				AlarmEnable,
				hdc2000c01v1OutCf
				Cf1,
				hdc2000c01v1OutCfTrapEnable
				AlarmEnable,
				hdc2000c01v1InAfdExpct
				Afd1,
				hdc2000c01v1InAfdExpctTrapEnable
				AlarmEnable,
				hdc2000c01v1InCfExpct
				Cf1,
				hdc2000c01v1InCfExpctTrapEnable
				AlarmEnable,
				hdc2000c01v1OutsdEnaS2016
				Bit0No1Yes,
				hdc2000c01v1OutsdEnaVii
				Bit0No1Yes,
				hdc2000c01v1OutsdEnaWss
				Bit0No1Yes,
				hdc2000c01v1OutsdEnaVitc
				Bit0No1Yes,
				hdc2000c01v1OutsdEnaTxt
				Bit0No1Yes,
				hdc2000c01v1SelAudPair0
				AudioMxInput5,
				hdc2000c01v1SelAudPair1
				AudioMxInput5,
				hdc2000c01v1SelAudPair2
				AudioMxInput5,
				hdc2000c01v1SelAudPair3
				AudioMxInput5,
				hdc2000c01v1SelAudPair4
				AudioMxInput5,
				hdc2000c01v1SelAudPair5
				AudioMxInput5,
				hdc2000c01v1SelAudPair6
				AudioMxInput5,
				hdc2000c01v1SelAudPair7
				AudioMxInput5,
				hdc2000c01v1VDelaySd
				DelayLines2,
				hdc2000c01v1HDelaySd
				DelayPixel5,
				hdc2000c01v1Grp1P0Gain
				Gain24dbMute,
				hdc2000c01v1Grp1P0Phase
				Bit0Nor1Inv,
				hdc2000c01v1Grp1P1Gain
				Gain24dbMute,
				hdc2000c01v1Grp1P1Phase
				Bit0Nor1Inv,
				hdc2000c01v1Grp2P0Gain
				Gain24dbMute,
				hdc2000c01v1Grp2P0Phase
				Bit0Nor1Inv,
				hdc2000c01v1Grp2P1Gain
				Gain24dbMute,
				hdc2000c01v1Grp2P1Phase
				Bit0Nor1Inv,
				hdc2000c01v1Grp3P0Gain
				Gain24dbMute,
				hdc2000c01v1Grp3P0Phase
				Bit0Nor1Inv,
				hdc2000c01v1Grp3P1Gain
				Gain24dbMute,
				hdc2000c01v1Grp3P1Phase
				Bit0Nor1Inv,
				hdc2000c01v1Grp4P0Gain
				Gain24dbMute,
				hdc2000c01v1Grp4P0Phase
				Bit0Nor1Inv,
				hdc2000c01v1Grp4P1Gain
				Gain24dbMute,
				hdc2000c01v1Grp4P1Phase
				Bit0Nor1Inv,
				hdc2000c01v1InAfdDetct
				Afd1,
				hdc2000c01v1InAfdDetctTrapEnable
				AlarmEnable,
				hdc2000c01v1InCfDetct
				Cf1,
				hdc2000c01v1InCfDetctTrapEnable
				AlarmEnable,
				hdc2000c01v1InPhyFail
				BitFail,
				hdc2000c01v1InPhyFailTrapEnable
				AlarmEnable,
				hdc2000c01v1InFmtFail
				BitFail,
				hdc2000c01v1InFmtFailTrapEnable
				AlarmEnable,
				hdc2000c01v1InIncFail
				BitFail,
				hdc2000c01v1InIncFailTrapEnable
				AlarmEnable,
				hdc2000c01v1InPresCrcFail
				BitFail,
				hdc2000c01v1InCrcFail
				BitFail,
				hdc2000c01v1InCrcFailTrapEnable
				AlarmEnable,
				hdc2000c01v1InPrsS352Fail
				BitFail,
				hdc2000c01v1InS352Fail
				BitFail,
				hdc2000c01v1PresS2016Fail
				BitFail,
				hdc2000c01v1ErrS2016Fail
				BitFail,
				hdc2000c01v1PresAudG1Fail
				BitFail,
				hdc2000c01v1PresAudG1FailTrapEnable
				AlarmEnable,
				hdc2000c01v1PresAudG2Fail
				BitFail,
				hdc2000c01v1PresAudG2FailTrapEnable
				AlarmEnable,
				hdc2000c01v1PresAudG3Fail
				BitFail,
				hdc2000c01v1PresAudG3FailTrapEnable
				AlarmEnable,
				hdc2000c01v1PresAudG4Fail
				BitFail,
				hdc2000c01v1PresAudG4FailTrapEnable
				AlarmEnable,
				hdc2000c01v1RefFail
				BitFail,
				hdc2000c01v1RefFailTrapEnable
				AlarmEnable,
				hdc2000c01v1RefFmtFail
				BitFail,
				hdc2000c01v1RefFmtFailTrapEnable
				AlarmEnable,
				hdc2000c01v1LockFail
				BitFail,
				hdc2000c01v1LockFailTrapEnable
				AlarmEnable,
				hdc2000c01v1AudPair0Fail
				BitFail,
				hdc2000c01v1AudPair0FailTrapEnable
				AlarmEnable,
				hdc2000c01v1AudPair1Fail
				BitFail,
				hdc2000c01v1AudPair1FailTrapEnable
				AlarmEnable,
				hdc2000c01v1AudPair2Fail
				BitFail,
				hdc2000c01v1AudPair2FailTrapEnable
				AlarmEnable,
				hdc2000c01v1AudPair3Fail
				BitFail,
				hdc2000c01v1AudPair3FailTrapEnable
				AlarmEnable,
				hdc2000c01v1AudPair4Fail
				BitFail,
				hdc2000c01v1AudPair4FailTrapEnable
				AlarmEnable,
				hdc2000c01v1AudPair5Fail
				BitFail,
				hdc2000c01v1AudPair5FailTrapEnable
				AlarmEnable,
				hdc2000c01v1AudPair6Fail
				BitFail,
				hdc2000c01v1AudPair6FailTrapEnable
				AlarmEnable,
				hdc2000c01v1AudPair7Fail
				BitFail,
				hdc2000c01v1AudPair7FailTrapEnable
				AlarmEnable,
				hdc2000c01v1InFormat
				SdiHd3gFmt3,
				hdc2000c01v1InFormatTrapEnable
				AlarmEnable,
				hdc2000c01v1RefFormat
				SdiHd3gFmt3,
				hdc2000c01v1RefFormatTrapEnable
				AlarmEnable,
				hdc2000c01v1MuteSd
				Bit0No1Yes,
				hdc2000c01v1BlackSd
				Bit0No1Yes,
				hdc2000c01v1SerialNo
				SerialNo,
				hdc2000c01v1OutsdEnaCea608
				Bit0No1Yes
			 }

		-- 1.3.6.1.4.1.10106.3.101291.1.1.1
		hdc2000c01v1Index OBJECT-TYPE
			SYNTAX ModuleIndex
			MAX-ACCESS read-only
			STATUS current
			DESCRIPTION
				"Index of HDC2000C01V1 Table"
		::= { hdc2000c01v1Entry 1 }

		-- 1.3.6.1.4.1.10106.3.101291.1.1.3
		hdc2000c01v1ActivePreset OBJECT-TYPE
			SYNTAX Preset16Active
			MAX-ACCESS read-only
			STATUS current
			DESCRIPTION
				"Shows the active preset"
		::= { hdc2000c01v1Entry 3 }

		-- 1.3.6.1.4.1.10106.3.101291.1.1.5
		hdc2000c01v1LoadPreset OBJECT-TYPE
			SYNTAX Preset16Load
			MAX-ACCESS read-write
			STATUS current
			DESCRIPTION
				"Allows loading a preset"
		::= { hdc2000c01v1Entry 5 }

		-- 1.3.6.1.4.1.10106.3.101291.1.1.7
		hdc2000c01v1SavePreset OBJECT-TYPE
			SYNTAX Preset16Save
			MAX-ACCESS read-write
			STATUS current
			DESCRIPTION
				"Allows saving a preset"
		::= { hdc2000c01v1Entry 7 }

		-- 1.3.6.1.4.1.10106.3.101291.1.1.9
		hdc2000c01v1AnaRefFmt OBJECT-TYPE
			SYNTAX SdiHd3gFmt5
			MAX-ACCESS read-write
			STATUS current
			DESCRIPTION
				"Analog reference input format"
		::= { hdc2000c01v1Entry 9 }

		-- 1.3.6.1.4.1.10106.3.101291.1.1.10
		hdc2000c01v1AnaRefFmtTrapEnable OBJECT-TYPE
			SYNTAX AlarmEnable
			MAX-ACCESS read-write
			STATUS current
			DESCRIPTION
				"Analog reference input format Trap Enable"
		::= { hdc2000c01v1Entry 10 }

		-- 1.3.6.1.4.1.10106.3.101291.1.1.11
		hdc2000c01v1GenlockMode OBJECT-TYPE
			SYNTAX GenlockM0de2
			MAX-ACCESS read-write
			STATUS current
			DESCRIPTION
				"Allos selecting the reference input signal"
		::= { hdc2000c01v1Entry 11 }

		-- 1.3.6.1.4.1.10106.3.101291.1.1.13
		hdc2000c01v1EnaAud20Bit OBJECT-TYPE
			SYNTAX Bit0No1Yes
			MAX-ACCESS read-write
			STATUS current
			DESCRIPTION
				"Enable 20-bit audio instead of 24-bit"
		::= { hdc2000c01v1Entry 13 }

		-- 1.3.6.1.4.1.10106.3.101291.1.1.15
		hdc2000c01v1ModeConv OBJECT-TYPE
			SYNTAX Bit0Aut1Man
			MAX-ACCESS read-write
			STATUS current
			DESCRIPTION
				"Conversion mode"
		::= { hdc2000c01v1Entry 15 }

		-- 1.3.6.1.4.1.10106.3.101291.1.1.16
		hdc2000c01v1ModeConvTrapEnable OBJECT-TYPE
			SYNTAX AlarmEnable
			MAX-ACCESS read-write
			STATUS current
			DESCRIPTION
				"Conversion mode Trap Enable"
		::= { hdc2000c01v1Entry 16 }

		-- 1.3.6.1.4.1.10106.3.101291.1.1.17
		hdc2000c01v1OutAfd OBJECT-TYPE
			SYNTAX Afd1
			MAX-ACCESS read-write
			STATUS current
			DESCRIPTION
				"Output active format description"
		::= { hdc2000c01v1Entry 17 }

		-- 1.3.6.1.4.1.10106.3.101291.1.1.18
		hdc2000c01v1OutAfdTrapEnable OBJECT-TYPE
			SYNTAX AlarmEnable
			MAX-ACCESS read-write
			STATUS current
			DESCRIPTION
				"Output active format description Trap Enable"
		::= { hdc2000c01v1Entry 18 }

		-- 1.3.6.1.4.1.10106.3.101291.1.1.19
		hdc2000c01v1OutCf OBJECT-TYPE
			SYNTAX Cf1
			MAX-ACCESS read-write
			STATUS current
			DESCRIPTION
				"Output coded frame"
		::= { hdc2000c01v1Entry 19 }

		-- 1.3.6.1.4.1.10106.3.101291.1.1.20
		hdc2000c01v1OutCfTrapEnable OBJECT-TYPE
			SYNTAX AlarmEnable
			MAX-ACCESS read-write
			STATUS current
			DESCRIPTION
				"Output coded frame Trap Enable"
		::= { hdc2000c01v1Entry 20 }

		-- 1.3.6.1.4.1.10106.3.101291.1.1.21
		hdc2000c01v1InAfdExpct OBJECT-TYPE
			SYNTAX Afd1
			MAX-ACCESS read-write
			STATUS current
			DESCRIPTION
				"Input expected active format description"
		::= { hdc2000c01v1Entry 21 }

		-- 1.3.6.1.4.1.10106.3.101291.1.1.22
		hdc2000c01v1InAfdExpctTrapEnable OBJECT-TYPE
			SYNTAX AlarmEnable
			MAX-ACCESS read-write
			STATUS current
			DESCRIPTION
				"Input expected active format description Trap Enable"
		::= { hdc2000c01v1Entry 22 }

		-- 1.3.6.1.4.1.10106.3.101291.1.1.23
		hdc2000c01v1InCfExpct OBJECT-TYPE
			SYNTAX Cf1
			MAX-ACCESS read-write
			STATUS current
			DESCRIPTION
				"Input expected coded frame"
		::= { hdc2000c01v1Entry 23 }

		-- 1.3.6.1.4.1.10106.3.101291.1.1.24
		hdc2000c01v1InCfExpctTrapEnable OBJECT-TYPE
			SYNTAX AlarmEnable
			MAX-ACCESS read-write
			STATUS current
			DESCRIPTION
				"Input expected coded frame Trap Enable"
		::= { hdc2000c01v1Entry 24 }

		-- 1.3.6.1.4.1.10106.3.101291.1.1.25
		hdc2000c01v1OutsdEnaS2016 OBJECT-TYPE
			SYNTAX Bit0No1Yes
			MAX-ACCESS read-write
			STATUS current
			DESCRIPTION
				"Enables insertion of SMPTE 2016 packets in  OUTSD"
		::= { hdc2000c01v1Entry 25 }

		-- 1.3.6.1.4.1.10106.3.101291.1.1.27
		hdc2000c01v1OutsdEnaVii OBJECT-TYPE
			SYNTAX Bit0No1Yes
			MAX-ACCESS read-write
			STATUS current
			DESCRIPTION
				"Enables insertion of VII in OUTSD"
		::= { hdc2000c01v1Entry 27 }

		-- 1.3.6.1.4.1.10106.3.101291.1.1.29
		hdc2000c01v1OutsdEnaWss OBJECT-TYPE
			SYNTAX Bit0No1Yes
			MAX-ACCESS read-write
			STATUS current
			DESCRIPTION
				"Enables insertion of WSS in OUTSD"
		::= { hdc2000c01v1Entry 29 }

		-- 1.3.6.1.4.1.10106.3.101291.1.1.31
		hdc2000c01v1OutsdEnaVitc OBJECT-TYPE
			SYNTAX Bit0No1Yes
			MAX-ACCESS read-write
			STATUS current
			DESCRIPTION
				"Enables insertion of VITC in OUTSD"
		::= { hdc2000c01v1Entry 31 }

		-- 1.3.6.1.4.1.10106.3.101291.1.1.33
		hdc2000c01v1OutsdEnaTxt OBJECT-TYPE
			SYNTAX Bit0No1Yes
			MAX-ACCESS read-write
			STATUS current
			DESCRIPTION
				"Enables insertion of TXT in OUTSD"
		::= { hdc2000c01v1Entry 33 }

		-- 1.3.6.1.4.1.10106.3.101291.1.1.35
		hdc2000c01v1SelAudPair0 OBJECT-TYPE
			SYNTAX AudioMxInput5
			MAX-ACCESS read-write
			STATUS current
			DESCRIPTION
				"Selection of output audio for pair 0"
		::= { hdc2000c01v1Entry 35 }

		-- 1.3.6.1.4.1.10106.3.101291.1.1.37
		hdc2000c01v1SelAudPair1 OBJECT-TYPE
			SYNTAX AudioMxInput5
			MAX-ACCESS read-write
			STATUS current
			DESCRIPTION
				"Selection of output audio for pair 1"
		::= { hdc2000c01v1Entry 37 }

		-- 1.3.6.1.4.1.10106.3.101291.1.1.39
		hdc2000c01v1SelAudPair2 OBJECT-TYPE
			SYNTAX AudioMxInput5
			MAX-ACCESS read-write
			STATUS current
			DESCRIPTION
				"Selection of output audio for pair 2"
		::= { hdc2000c01v1Entry 39 }

		-- 1.3.6.1.4.1.10106.3.101291.1.1.41
		hdc2000c01v1SelAudPair3 OBJECT-TYPE
			SYNTAX AudioMxInput5
			MAX-ACCESS read-write
			STATUS current
			DESCRIPTION
				"Selection of output audio for pair 3"
		::= { hdc2000c01v1Entry 41 }

		-- 1.3.6.1.4.1.10106.3.101291.1.1.43
		hdc2000c01v1SelAudPair4 OBJECT-TYPE
			SYNTAX AudioMxInput5
			MAX-ACCESS read-write
			STATUS current
			DESCRIPTION
				"Selection of output audio for pair 4"
		::= { hdc2000c01v1Entry 43 }

		-- 1.3.6.1.4.1.10106.3.101291.1.1.45
		hdc2000c01v1SelAudPair5 OBJECT-TYPE
			SYNTAX AudioMxInput5
			MAX-ACCESS read-write
			STATUS current
			DESCRIPTION
				"Selection of output audio for pair 5"
		::= { hdc2000c01v1Entry 45 }

		-- 1.3.6.1.4.1.10106.3.101291.1.1.47
		hdc2000c01v1SelAudPair6 OBJECT-TYPE
			SYNTAX AudioMxInput5
			MAX-ACCESS read-write
			STATUS current
			DESCRIPTION
				"Selection of output audio for pair 6"
		::= { hdc2000c01v1Entry 47 }

		-- 1.3.6.1.4.1.10106.3.101291.1.1.49
		hdc2000c01v1SelAudPair7 OBJECT-TYPE
			SYNTAX AudioMxInput5
			MAX-ACCESS read-write
			STATUS current
			DESCRIPTION
				"Selection of output audio for pair 7"
		::= { hdc2000c01v1Entry 49 }

		-- 1.3.6.1.4.1.10106.3.101291.1.1.51
		hdc2000c01v1VDelaySd OBJECT-TYPE
			SYNTAX DelayLines2
			MAX-ACCESS read-write
			STATUS current
			DESCRIPTION
				"Allows adjusting the SD downconverted video vertical delay"
		::= { hdc2000c01v1Entry 51 }

		-- 1.3.6.1.4.1.10106.3.101291.1.1.53
		hdc2000c01v1HDelaySd OBJECT-TYPE
			SYNTAX DelayPixel5
			MAX-ACCESS read-write
			STATUS current
			DESCRIPTION
				"Allows adjusting the SD downconverted video horizontal delay"
		::= { hdc2000c01v1Entry 53 }

		-- 1.3.6.1.4.1.10106.3.101291.1.1.55
		hdc2000c01v1Grp1P0Gain OBJECT-TYPE
			SYNTAX Gain24dbMute
			MAX-ACCESS read-write
			STATUS current
			DESCRIPTION
				"Group 1 pair 0 gain"
		::= { hdc2000c01v1Entry 55 }

		-- 1.3.6.1.4.1.10106.3.101291.1.1.57
		hdc2000c01v1Grp1P0Phase OBJECT-TYPE
			SYNTAX Bit0Nor1Inv
			MAX-ACCESS read-write
			STATUS current
			DESCRIPTION
				"Group 1 pair 0 phase"
		::= { hdc2000c01v1Entry 57 }

		-- 1.3.6.1.4.1.10106.3.101291.1.1.59
		hdc2000c01v1Grp1P1Gain OBJECT-TYPE
			SYNTAX Gain24dbMute
			MAX-ACCESS read-write
			STATUS current
			DESCRIPTION
				"Group 1 pair 1 gain"
		::= { hdc2000c01v1Entry 59 }

		-- 1.3.6.1.4.1.10106.3.101291.1.1.61
		hdc2000c01v1Grp1P1Phase OBJECT-TYPE
			SYNTAX Bit0Nor1Inv
			MAX-ACCESS read-write
			STATUS current
			DESCRIPTION
				"Group 1 pair 1 phase"
		::= { hdc2000c01v1Entry 61 }

		-- 1.3.6.1.4.1.10106.3.101291.1.1.63
		hdc2000c01v1Grp2P0Gain OBJECT-TYPE
			SYNTAX Gain24dbMute
			MAX-ACCESS read-write
			STATUS current
			DESCRIPTION
				"Group 2 pair 0 gain"
		::= { hdc2000c01v1Entry 63 }

		-- 1.3.6.1.4.1.10106.3.101291.1.1.65
		hdc2000c01v1Grp2P0Phase OBJECT-TYPE
			SYNTAX Bit0Nor1Inv
			MAX-ACCESS read-write
			STATUS current
			DESCRIPTION
				"Group 2 pair 0 phase"
		::= { hdc2000c01v1Entry 65 }

		-- 1.3.6.1.4.1.10106.3.101291.1.1.67
		hdc2000c01v1Grp2P1Gain OBJECT-TYPE
			SYNTAX Gain24dbMute
			MAX-ACCESS read-write
			STATUS current
			DESCRIPTION
				"Group 2 pair 1 gain"
		::= { hdc2000c01v1Entry 67 }

		-- 1.3.6.1.4.1.10106.3.101291.1.1.69
		hdc2000c01v1Grp2P1Phase OBJECT-TYPE
			SYNTAX Bit0Nor1Inv
			MAX-ACCESS read-write
			STATUS current
			DESCRIPTION
				"Group 2 pair 1 phase"
		::= { hdc2000c01v1Entry 69 }

		-- 1.3.6.1.4.1.10106.3.101291.1.1.71
		hdc2000c01v1Grp3P0Gain OBJECT-TYPE
			SYNTAX Gain24dbMute
			MAX-ACCESS read-write
			STATUS current
			DESCRIPTION
				"Group 3 pair 0 gain"
		::= { hdc2000c01v1Entry 71 }

		-- 1.3.6.1.4.1.10106.3.101291.1.1.73
		hdc2000c01v1Grp3P0Phase OBJECT-TYPE
			SYNTAX Bit0Nor1Inv
			MAX-ACCESS read-write
			STATUS current
			DESCRIPTION
				"Group 3 pair 0 phase"
		::= { hdc2000c01v1Entry 73 }

		-- 1.3.6.1.4.1.10106.3.101291.1.1.75
		hdc2000c01v1Grp3P1Gain OBJECT-TYPE
			SYNTAX Gain24dbMute
			MAX-ACCESS read-write
			STATUS current
			DESCRIPTION
				"Group 3 pair 1 gain"
		::= { hdc2000c01v1Entry 75 }

		-- 1.3.6.1.4.1.10106.3.101291.1.1.77
		hdc2000c01v1Grp3P1Phase OBJECT-TYPE
			SYNTAX Bit0Nor1Inv
			MAX-ACCESS read-write
			STATUS current
			DESCRIPTION
				"Group 3 pair 1 phase"
		::= { hdc2000c01v1Entry 77 }

		-- 1.3.6.1.4.1.10106.3.101291.1.1.79
		hdc2000c01v1Grp4P0Gain OBJECT-TYPE
			SYNTAX Gain24dbMute
			MAX-ACCESS read-write
			STATUS current
			DESCRIPTION
				"Group 4 pair 0 gain"
		::= { hdc2000c01v1Entry 79 }

		-- 1.3.6.1.4.1.10106.3.101291.1.1.81
		hdc2000c01v1Grp4P0Phase OBJECT-TYPE
			SYNTAX Bit0Nor1Inv
			MAX-ACCESS read-write
			STATUS current
			DESCRIPTION
				"Group 4 pair 0 phase"
		::= { hdc2000c01v1Entry 81 }

		-- 1.3.6.1.4.1.10106.3.101291.1.1.83
		hdc2000c01v1Grp4P1Gain OBJECT-TYPE
			SYNTAX Gain24dbMute
			MAX-ACCESS read-write
			STATUS current
			DESCRIPTION
				"Group 4 pair 1 gain"
		::= { hdc2000c01v1Entry 83 }

		-- 1.3.6.1.4.1.10106.3.101291.1.1.85
		hdc2000c01v1Grp4P1Phase OBJECT-TYPE
			SYNTAX Bit0Nor1Inv
			MAX-ACCESS read-write
			STATUS current
			DESCRIPTION
				"Group 4 pair 1 phase"
		::= { hdc2000c01v1Entry 85 }

		-- 1.3.6.1.4.1.10106.3.101291.1.1.87
		hdc2000c01v1InAfdDetct OBJECT-TYPE
			SYNTAX Afd1
			MAX-ACCESS read-only
			STATUS current
			DESCRIPTION
				"Input detected AFD"
		::= { hdc2000c01v1Entry 87 }

		-- 1.3.6.1.4.1.10106.3.101291.1.1.88
		hdc2000c01v1InAfdDetctTrapEnable OBJECT-TYPE
			SYNTAX AlarmEnable
			MAX-ACCESS read-write
			STATUS current
			DESCRIPTION
				"Input detected AFD Trap Enable"
		::= { hdc2000c01v1Entry 88 }

		-- 1.3.6.1.4.1.10106.3.101291.1.1.89
		hdc2000c01v1InCfDetct OBJECT-TYPE
			SYNTAX Cf1
			MAX-ACCESS read-only
			STATUS current
			DESCRIPTION
				"Input detected coded frame"
		::= { hdc2000c01v1Entry 89 }

		-- 1.3.6.1.4.1.10106.3.101291.1.1.90
		hdc2000c01v1InCfDetctTrapEnable OBJECT-TYPE
			SYNTAX AlarmEnable
			MAX-ACCESS read-write
			STATUS current
			DESCRIPTION
				"Input detected coded frame Trap Enable"
		::= { hdc2000c01v1Entry 90 }

		-- 1.3.6.1.4.1.10106.3.101291.1.1.91
		hdc2000c01v1InPhyFail OBJECT-TYPE
			SYNTAX BitFail
			MAX-ACCESS read-only
			STATUS current
			DESCRIPTION
				"Absence fail"
		::= { hdc2000c01v1Entry 91 }

		-- 1.3.6.1.4.1.10106.3.101291.1.1.92
		hdc2000c01v1InPhyFailTrapEnable OBJECT-TYPE
			SYNTAX AlarmEnable
			MAX-ACCESS read-write
			STATUS current
			DESCRIPTION
				"Absence fail Trap Enable"
		::= { hdc2000c01v1Entry 92 }

		-- 1.3.6.1.4.1.10106.3.101291.1.1.93
		hdc2000c01v1InFmtFail OBJECT-TYPE
			SYNTAX BitFail
			MAX-ACCESS read-only
			STATUS current
			DESCRIPTION
				"Format fail"
		::= { hdc2000c01v1Entry 93 }

		-- 1.3.6.1.4.1.10106.3.101291.1.1.94
		hdc2000c01v1InFmtFailTrapEnable OBJECT-TYPE
			SYNTAX AlarmEnable
			MAX-ACCESS read-write
			STATUS current
			DESCRIPTION
				"Format fail Trap Enable"
		::= { hdc2000c01v1Entry 94 }

		-- 1.3.6.1.4.1.10106.3.101291.1.1.95
		hdc2000c01v1InIncFail OBJECT-TYPE
			SYNTAX BitFail
			MAX-ACCESS read-only
			STATUS current
			DESCRIPTION
				"Incompatible format fail"
		::= { hdc2000c01v1Entry 95 }

		-- 1.3.6.1.4.1.10106.3.101291.1.1.96
		hdc2000c01v1InIncFailTrapEnable OBJECT-TYPE
			SYNTAX AlarmEnable
			MAX-ACCESS read-write
			STATUS current
			DESCRIPTION
				"Incompatible format fail Trap Enable"
		::= { hdc2000c01v1Entry 96 }

		-- 1.3.6.1.4.1.10106.3.101291.1.1.97
		hdc2000c01v1InPresCrcFail OBJECT-TYPE
			SYNTAX BitFail
			MAX-ACCESS read-only
			STATUS current
			DESCRIPTION
				"EDH/CRC presence fail"
		::= { hdc2000c01v1Entry 97 }

		-- 1.3.6.1.4.1.10106.3.101291.1.1.99
		hdc2000c01v1InCrcFail OBJECT-TYPE
			SYNTAX BitFail
			MAX-ACCESS read-only
			STATUS current
			DESCRIPTION
				"EDH/CRC fail"
		::= { hdc2000c01v1Entry 99 }

		-- 1.3.6.1.4.1.10106.3.101291.1.1.100
		hdc2000c01v1InCrcFailTrapEnable OBJECT-TYPE
			SYNTAX AlarmEnable
			MAX-ACCESS read-write
			STATUS current
			DESCRIPTION
				"EDH/CRC fail Trap Enable"
		::= { hdc2000c01v1Entry 100 }

		-- 1.3.6.1.4.1.10106.3.101291.1.1.101
		hdc2000c01v1InPrsS352Fail OBJECT-TYPE
			SYNTAX BitFail
			MAX-ACCESS read-only
			STATUS current
			DESCRIPTION
				"SMPTE 352 presence fail"
		::= { hdc2000c01v1Entry 101 }

		-- 1.3.6.1.4.1.10106.3.101291.1.1.103
		hdc2000c01v1InS352Fail OBJECT-TYPE
			SYNTAX BitFail
			MAX-ACCESS read-only
			STATUS current
			DESCRIPTION
				"SMPTE 352 fail"
		::= { hdc2000c01v1Entry 103 }

		-- 1.3.6.1.4.1.10106.3.101291.1.1.105
		hdc2000c01v1PresS2016Fail OBJECT-TYPE
			SYNTAX BitFail
			MAX-ACCESS read-only
			STATUS current
			DESCRIPTION
				"SMPTE 2016 presence fail"
		::= { hdc2000c01v1Entry 105 }

		-- 1.3.6.1.4.1.10106.3.101291.1.1.107
		hdc2000c01v1ErrS2016Fail OBJECT-TYPE
			SYNTAX BitFail
			MAX-ACCESS read-only
			STATUS current
			DESCRIPTION
				"SMPTE 2016 error fail"
		::= { hdc2000c01v1Entry 107 }

		-- 1.3.6.1.4.1.10106.3.101291.1.1.109
		hdc2000c01v1PresAudG1Fail OBJECT-TYPE
			SYNTAX BitFail
			MAX-ACCESS read-only
			STATUS current
			DESCRIPTION
				"Audio group 1 presence fail"
		::= { hdc2000c01v1Entry 109 }

		-- 1.3.6.1.4.1.10106.3.101291.1.1.110
		hdc2000c01v1PresAudG1FailTrapEnable OBJECT-TYPE
			SYNTAX AlarmEnable
			MAX-ACCESS read-write
			STATUS current
			DESCRIPTION
				"Audio group 1 presence fail Trap Enable"
		::= { hdc2000c01v1Entry 110 }

		-- 1.3.6.1.4.1.10106.3.101291.1.1.111
		hdc2000c01v1PresAudG2Fail OBJECT-TYPE
			SYNTAX BitFail
			MAX-ACCESS read-only
			STATUS current
			DESCRIPTION
				"Audio group 2 presence fail"
		::= { hdc2000c01v1Entry 111 }

		-- 1.3.6.1.4.1.10106.3.101291.1.1.112
		hdc2000c01v1PresAudG2FailTrapEnable OBJECT-TYPE
			SYNTAX AlarmEnable
			MAX-ACCESS read-write
			STATUS current
			DESCRIPTION
				"Audio group 2 presence fail Trap Enable"
		::= { hdc2000c01v1Entry 112 }

		-- 1.3.6.1.4.1.10106.3.101291.1.1.113
		hdc2000c01v1PresAudG3Fail OBJECT-TYPE
			SYNTAX BitFail
			MAX-ACCESS read-only
			STATUS current
			DESCRIPTION
				"Audio group 3 presence fail"
		::= { hdc2000c01v1Entry 113 }

		-- 1.3.6.1.4.1.10106.3.101291.1.1.114
		hdc2000c01v1PresAudG3FailTrapEnable OBJECT-TYPE
			SYNTAX AlarmEnable
			MAX-ACCESS read-write
			STATUS current
			DESCRIPTION
				"Audio group 3 presence fail Trap Enable"
		::= { hdc2000c01v1Entry 114 }

		-- 1.3.6.1.4.1.10106.3.101291.1.1.115
		hdc2000c01v1PresAudG4Fail OBJECT-TYPE
			SYNTAX BitFail
			MAX-ACCESS read-only
			STATUS current
			DESCRIPTION
				"Audio group 4 presence fail"
		::= { hdc2000c01v1Entry 115 }

		-- 1.3.6.1.4.1.10106.3.101291.1.1.116
		hdc2000c01v1PresAudG4FailTrapEnable OBJECT-TYPE
			SYNTAX AlarmEnable
			MAX-ACCESS read-write
			STATUS current
			DESCRIPTION
				"Audio group 4 presence fail Trap Enable"
		::= { hdc2000c01v1Entry 116 }

		-- 1.3.6.1.4.1.10106.3.101291.1.1.117
		hdc2000c01v1RefFail OBJECT-TYPE
			SYNTAX BitFail
			MAX-ACCESS read-only
			STATUS current
			DESCRIPTION
				"Analog reference absence fail"
		::= { hdc2000c01v1Entry 117 }

		-- 1.3.6.1.4.1.10106.3.101291.1.1.118
		hdc2000c01v1RefFailTrapEnable OBJECT-TYPE
			SYNTAX AlarmEnable
			MAX-ACCESS read-write
			STATUS current
			DESCRIPTION
				"Analog reference absence fail Trap Enable"
		::= { hdc2000c01v1Entry 118 }

		-- 1.3.6.1.4.1.10106.3.101291.1.1.119
		hdc2000c01v1RefFmtFail OBJECT-TYPE
			SYNTAX BitFail
			MAX-ACCESS read-only
			STATUS current
			DESCRIPTION
				"Analog reference format fail"
		::= { hdc2000c01v1Entry 119 }

		-- 1.3.6.1.4.1.10106.3.101291.1.1.120
		hdc2000c01v1RefFmtFailTrapEnable OBJECT-TYPE
			SYNTAX AlarmEnable
			MAX-ACCESS read-write
			STATUS current
			DESCRIPTION
				"Analog reference format fail Trap Enable"
		::= { hdc2000c01v1Entry 120 }

		-- 1.3.6.1.4.1.10106.3.101291.1.1.121
		hdc2000c01v1LockFail OBJECT-TYPE
			SYNTAX BitFail
			MAX-ACCESS read-only
			STATUS current
			DESCRIPTION
				"Reference unlock fail"
		::= { hdc2000c01v1Entry 121 }

		-- 1.3.6.1.4.1.10106.3.101291.1.1.122
		hdc2000c01v1LockFailTrapEnable OBJECT-TYPE
			SYNTAX AlarmEnable
			MAX-ACCESS read-write
			STATUS current
			DESCRIPTION
				"Reference unlock fail Trap Enable"
		::= { hdc2000c01v1Entry 122 }

		-- 1.3.6.1.4.1.10106.3.101291.1.1.123
		hdc2000c01v1AudPair0Fail OBJECT-TYPE
			SYNTAX BitFail
			MAX-ACCESS read-only
			STATUS current
			DESCRIPTION
				"Audio pair 0 fail"
		::= { hdc2000c01v1Entry 123 }

		-- 1.3.6.1.4.1.10106.3.101291.1.1.124
		hdc2000c01v1AudPair0FailTrapEnable OBJECT-TYPE
			SYNTAX AlarmEnable
			MAX-ACCESS read-write
			STATUS current
			DESCRIPTION
				"Audio pair 0 fail Trap Enable"
		::= { hdc2000c01v1Entry 124 }

		-- 1.3.6.1.4.1.10106.3.101291.1.1.125
		hdc2000c01v1AudPair1Fail OBJECT-TYPE
			SYNTAX BitFail
			MAX-ACCESS read-only
			STATUS current
			DESCRIPTION
				"Audio pair 1 fail"
		::= { hdc2000c01v1Entry 125 }

		-- 1.3.6.1.4.1.10106.3.101291.1.1.126
		hdc2000c01v1AudPair1FailTrapEnable OBJECT-TYPE
			SYNTAX AlarmEnable
			MAX-ACCESS read-write
			STATUS current
			DESCRIPTION
				"Audio pair 1 fail Trap Enable"
		::= { hdc2000c01v1Entry 126 }

		-- 1.3.6.1.4.1.10106.3.101291.1.1.127
		hdc2000c01v1AudPair2Fail OBJECT-TYPE
			SYNTAX BitFail
			MAX-ACCESS read-only
			STATUS current
			DESCRIPTION
				"Audio pair 2 fail"
		::= { hdc2000c01v1Entry 127 }

		-- 1.3.6.1.4.1.10106.3.101291.1.1.128
		hdc2000c01v1AudPair2FailTrapEnable OBJECT-TYPE
			SYNTAX AlarmEnable
			MAX-ACCESS read-write
			STATUS current
			DESCRIPTION
				"Audio pair 2 fail Trap Enable"
		::= { hdc2000c01v1Entry 128 }

		-- 1.3.6.1.4.1.10106.3.101291.1.1.129
		hdc2000c01v1AudPair3Fail OBJECT-TYPE
			SYNTAX BitFail
			MAX-ACCESS read-only
			STATUS current
			DESCRIPTION
				"Audio pair 3 fail"
		::= { hdc2000c01v1Entry 129 }

		-- 1.3.6.1.4.1.10106.3.101291.1.1.130
		hdc2000c01v1AudPair3FailTrapEnable OBJECT-TYPE
			SYNTAX AlarmEnable
			MAX-ACCESS read-write
			STATUS current
			DESCRIPTION
				"Audio pair 3 fail Trap Enable"
		::= { hdc2000c01v1Entry 130 }

		-- 1.3.6.1.4.1.10106.3.101291.1.1.131
		hdc2000c01v1AudPair4Fail OBJECT-TYPE
			SYNTAX BitFail
			MAX-ACCESS read-only
			STATUS current
			DESCRIPTION
				"Audio pair 4 fail"
		::= { hdc2000c01v1Entry 131 }

		-- 1.3.6.1.4.1.10106.3.101291.1.1.132
		hdc2000c01v1AudPair4FailTrapEnable OBJECT-TYPE
			SYNTAX AlarmEnable
			MAX-ACCESS read-write
			STATUS current
			DESCRIPTION
				"Audio pair 4 fail Trap Enable"
		::= { hdc2000c01v1Entry 132 }

		-- 1.3.6.1.4.1.10106.3.101291.1.1.133
		hdc2000c01v1AudPair5Fail OBJECT-TYPE
			SYNTAX BitFail
			MAX-ACCESS read-only
			STATUS current
			DESCRIPTION
				"Audio pair 5 fail"
		::= { hdc2000c01v1Entry 133 }

		-- 1.3.6.1.4.1.10106.3.101291.1.1.134
		hdc2000c01v1AudPair5FailTrapEnable OBJECT-TYPE
			SYNTAX AlarmEnable
			MAX-ACCESS read-write
			STATUS current
			DESCRIPTION
				"Audio pair 5 fail Trap Enable"
		::= { hdc2000c01v1Entry 134 }

		-- 1.3.6.1.4.1.10106.3.101291.1.1.135
		hdc2000c01v1AudPair6Fail OBJECT-TYPE
			SYNTAX BitFail
			MAX-ACCESS read-only
			STATUS current
			DESCRIPTION
				"Audio pair 6 fail"
		::= { hdc2000c01v1Entry 135 }

		-- 1.3.6.1.4.1.10106.3.101291.1.1.136
		hdc2000c01v1AudPair6FailTrapEnable OBJECT-TYPE
			SYNTAX AlarmEnable
			MAX-ACCESS read-write
			STATUS current
			DESCRIPTION
				"Audio pair 6 fail Trap Enable"
		::= { hdc2000c01v1Entry 136 }

		-- 1.3.6.1.4.1.10106.3.101291.1.1.137
		hdc2000c01v1AudPair7Fail OBJECT-TYPE
			SYNTAX BitFail
			MAX-ACCESS read-only
			STATUS current
			DESCRIPTION
				"Audio pair 7 fail"
		::= { hdc2000c01v1Entry 137 }

		-- 1.3.6.1.4.1.10106.3.101291.1.1.138
		hdc2000c01v1AudPair7FailTrapEnable OBJECT-TYPE
			SYNTAX AlarmEnable
			MAX-ACCESS read-write
			STATUS current
			DESCRIPTION
				"Audio pair 7 fail Trap Enable"
		::= { hdc2000c01v1Entry 138 }

		-- 1.3.6.1.4.1.10106.3.101291.1.1.139
		hdc2000c01v1InFormat OBJECT-TYPE
			SYNTAX SdiHd3gFmt3
			MAX-ACCESS read-only
			STATUS current
			DESCRIPTION
				"Input format"
		::= { hdc2000c01v1Entry 139 }

		-- 1.3.6.1.4.1.10106.3.101291.1.1.140
		hdc2000c01v1InFormatTrapEnable OBJECT-TYPE
			SYNTAX AlarmEnable
			MAX-ACCESS read-write
			STATUS current
			DESCRIPTION
				"Input format Trap Enable"
		::= { hdc2000c01v1Entry 140 }

		-- 1.3.6.1.4.1.10106.3.101291.1.1.141
		hdc2000c01v1RefFormat OBJECT-TYPE
			SYNTAX SdiHd3gFmt3
			MAX-ACCESS read-only
			STATUS current
			DESCRIPTION
				"Reference format"
		::= { hdc2000c01v1Entry 141 }

		-- 1.3.6.1.4.1.10106.3.101291.1.1.142
		hdc2000c01v1RefFormatTrapEnable OBJECT-TYPE
			SYNTAX AlarmEnable
			MAX-ACCESS read-write
			STATUS current
			DESCRIPTION
				"Reference format Trap Enable"
		::= { hdc2000c01v1Entry 142 }

		-- 1.3.6.1.4.1.10106.3.101291.1.1.143
		hdc2000c01v1MuteSd OBJECT-TYPE
			SYNTAX Bit0No1Yes
			MAX-ACCESS read-only
			STATUS current
			DESCRIPTION
				"Muted SD output"
		::= { hdc2000c01v1Entry 143 }

		-- 1.3.6.1.4.1.10106.3.101291.1.1.145
		hdc2000c01v1BlackSd OBJECT-TYPE
			SYNTAX Bit0No1Yes
			MAX-ACCESS read-only
			STATUS current
			DESCRIPTION
				"Black SD output"
		::= { hdc2000c01v1Entry 145 }

		-- 1.3.6.1.4.1.10106.3.101291.1.1.147
		hdc2000c01v1SerialNo OBJECT-TYPE
			SYNTAX SerialNo
			MAX-ACCESS read-only
			STATUS current
			DESCRIPTION
				"Serial number"
		::= { hdc2000c01v1Entry 147 }

		-- 1.3.6.1.4.1.10106.3.101291.1.1.149
		hdc2000c01v1OutsdEnaCea608 OBJECT-TYPE
			SYNTAX Bit0No1Yes
			MAX-ACCESS read-write
			STATUS current
			DESCRIPTION
				"Enables insertion of CEA608 in OUTSD"
		::= { hdc2000c01v1Entry 149 }

		-- 1.3.6.1.4.1.10106.3.442701
		gps3002c04v1 OBJECT IDENTIFIER ::= { albalaProducts 442701 }

		-- 1.3.6.1.4.1.10106.3.442701.1
		gps3002c04v1Table  OBJECT-TYPE
			SYNTAX SEQUENCE OF Gps3002c04v1Entry
			MAX-ACCESS not-accessible
			STATUS current
			DESCRIPTION
				"Module  GPS3002C04V1 Table"
			::= { gps3002c04v1 1 }

		-- 1.3.6.1.4.1.10106.3.442701.1.1
		gps3002c04v1Entry  OBJECT-TYPE
			SYNTAX Gps3002c04v1Entry
			MAX-ACCESS not-accessible
			STATUS current
			DESCRIPTION
				"Module GPS3002C04V1 Entry"
			INDEX { gps3002c04v1Index }
			::= { gps3002c04v1Table 1 }

			Gps3002c04v1Entry ::=
			SEQUENCE {
				gps3002c04v1Index
				ModuleIndex,
				gps3002c04v1Holdover
				Bit0Dis1Ena,
				gps3002c04v1RedundanceMode
				ChgOverMode3,
				gps3002c04v1RedundanceModeTrapEnable
				AlarmEnable,
				gps3002c04v1CableDelay
				DelayX2Ns,
				gps3002c04v1HoldoverStat
				Bit0Trk1Hol,
				gps3002c04v1HoldoverStatTrapEnable
				AlarmEnable,
				gps3002c04v1MaintenanceFail
				Bit0No1Yes,
				gps3002c04v1MaintenanceFailTrapEnable
				AlarmEnable,
				gps3002c04v1OutputsMuted
				BitFail,
				gps3002c04v1OutputsMutedTrapEnable
				AlarmEnable,
				gps3002c04v11ppsDisable
				BitFail,
				gps3002c04v11ppsDisableTrapEnable
				AlarmEnable,
				gps3002c04v1AdquisitionStat
				GpsAdqStat2,
				gps3002c04v1SatRxStat
				GpsSatRxStat,
				gps3002c04v1AntenaStat
				GpsAntenaStat,
				gps3002c04v1AntenaStatTrapEnable
				AlarmEnable,
				gps3002c04v1SatNoFail
				BitFail,
				gps3002c04v1GpsSiteSurv
				Bit0No1Yes,
				gps3002c04v1GpsTrackSats
				GpsSatellites,
				gps3002c04v1GpsVisibleSats
				GpsSatellites,
				gps3002c04v1GpsSignalLevel
				LevelDbHz,
				gps3002c04v1HoldoverTime
				GpsHoldovrTime,
				gps3002c04v1FreqDriftEst
				GpsFrqDrftEst,
				gps3002c04v1PhaseDriftEst
				GpsPhsDrftEst,
				gps3002c04v1SerialNo
				SerialNo
			 }

		-- 1.3.6.1.4.1.10106.3.101291.1.1.1
		gps3002c04v1Index OBJECT-TYPE
			SYNTAX ModuleIndex
			MAX-ACCESS read-only
			STATUS current
			DESCRIPTION
				"Index of GPS3002C04V1 Table"
		::= { gps3002c04v1Entry 1 }

		-- 1.3.6.1.4.1.10106.3.101291.1.1.3
		gps3002c04v1Holdover OBJECT-TYPE
			SYNTAX Bit0Dis1Ena
			MAX-ACCESS read-write
			STATUS current
			DESCRIPTION
				"Allows setting the module in the holdover mode"
		::= { gps3002c04v1Entry 3 }

		-- 1.3.6.1.4.1.10106.3.101291.1.1.5
		gps3002c04v1RedundanceMode OBJECT-TYPE
			SYNTAX ChgOverMode3
			MAX-ACCESS read-write
			STATUS current
			DESCRIPTION
				"Allows selecting the redundance mode"
		::= { gps3002c04v1Entry 5 }

		-- 1.3.6.1.4.1.10106.3.101291.1.1.6
		gps3002c04v1RedundanceModeTrapEnable OBJECT-TYPE
			SYNTAX AlarmEnable
			MAX-ACCESS read-write
			STATUS current
			DESCRIPTION
				"Allows selecting the redundance mode Trap Enable"
		::= { gps3002c04v1Entry 6 }

		-- 1.3.6.1.4.1.10106.3.101291.1.1.7
		gps3002c04v1CableDelay OBJECT-TYPE
			SYNTAX DelayX2Ns
			MAX-ACCESS read-write
			STATUS current
			DESCRIPTION
				"Allows compensating the antenna cable delay"
		::= { gps3002c04v1Entry 7 }

		-- 1.3.6.1.4.1.10106.3.101291.1.1.9
		gps3002c04v1HoldoverStat OBJECT-TYPE
			SYNTAX Bit0Trk1Hol
			MAX-ACCESS read-only
			STATUS current
			DESCRIPTION
				"Indicates if the module is locked to GPS or to reference or it is in holdover mode"
		::= { gps3002c04v1Entry 9 }

		-- 1.3.6.1.4.1.10106.3.101291.1.1.10
		gps3002c04v1HoldoverStatTrapEnable OBJECT-TYPE
			SYNTAX AlarmEnable
			MAX-ACCESS read-write
			STATUS current
			DESCRIPTION
				"Indicates if the module is locked to GPS or to reference or it is in holdover mode Trap Enable"
		::= { gps3002c04v1Entry 10 }

		-- 1.3.6.1.4.1.10106.3.101291.1.1.11
		gps3002c04v1MaintenanceFail OBJECT-TYPE
			SYNTAX Bit0No1Yes
			MAX-ACCESS read-only
			STATUS current
			DESCRIPTION
				"Indicates that a service operation is required"
		::= { gps3002c04v1Entry 11 }

		-- 1.3.6.1.4.1.10106.3.101291.1.1.12
		gps3002c04v1MaintenanceFailTrapEnable OBJECT-TYPE
			SYNTAX AlarmEnable
			MAX-ACCESS read-write
			STATUS current
			DESCRIPTION
				"Indicates that a service operation is required Trap Enable"
		::= { gps3002c04v1Entry 12 }

		-- 1.3.6.1.4.1.10106.3.101291.1.1.13
		gps3002c04v1OutputsMuted OBJECT-TYPE
			SYNTAX BitFail
			MAX-ACCESS read-only
			STATUS current
			DESCRIPTION
				"Indicates f the module outputs are disabled (reserve module)"
		::= { gps3002c04v1Entry 13 }

		-- 1.3.6.1.4.1.10106.3.101291.1.1.14
		gps3002c04v1OutputsMutedTrapEnable OBJECT-TYPE
			SYNTAX AlarmEnable
			MAX-ACCESS read-write
			STATUS current
			DESCRIPTION
				"Indicates f the module outputs are disabled (reserve module) Trap Enable"
		::= { gps3002c04v1Entry 14 }

		-- 1.3.6.1.4.1.10106.3.101291.1.1.15
		gps3002c04v11ppsDisable OBJECT-TYPE
			SYNTAX BitFail
			MAX-ACCESS read-only
			STATUS current
			DESCRIPTION
				"Indicates if the 1PPS output is muted"
		::= { gps3002c04v1Entry 15 }

		-- 1.3.6.1.4.1.10106.3.101291.1.1.16
		gps3002c04v11ppsDisableTrapEnable OBJECT-TYPE
			SYNTAX AlarmEnable
			MAX-ACCESS read-write
			STATUS current
			DESCRIPTION
				"Indicates if the 1PPS output is muted Trap Enable"
		::= { gps3002c04v1Entry 16 }

		-- 1.3.6.1.4.1.10106.3.101291.1.1.17
		gps3002c04v1AdquisitionStat OBJECT-TYPE
			SYNTAX GpsAdqStat2
			MAX-ACCESS read-only
			STATUS current
			DESCRIPTION
				"GPS3002 module adquisition status"
		::= { gps3002c04v1Entry 17 }

		-- 1.3.6.1.4.1.10106.3.101291.1.1.19
		gps3002c04v1SatRxStat OBJECT-TYPE
			SYNTAX GpsSatRxStat
			MAX-ACCESS read-only
			STATUS current
			DESCRIPTION
				"GPS receiver module satellite tracking status"
		::= { gps3002c04v1Entry 19 }

		-- 1.3.6.1.4.1.10106.3.101291.1.1.21
		gps3002c04v1AntenaStat OBJECT-TYPE
			SYNTAX GpsAntenaStat
			MAX-ACCESS read-only
			STATUS current
			DESCRIPTION
				"Antenna connection status"
		::= { gps3002c04v1Entry 21 }

		-- 1.3.6.1.4.1.10106.3.101291.1.1.22
		gps3002c04v1AntenaStatTrapEnable OBJECT-TYPE
			SYNTAX AlarmEnable
			MAX-ACCESS read-write
			STATUS current
			DESCRIPTION
				"Antenna connection status Trap Enable"
		::= { gps3002c04v1Entry 22 }

		-- 1.3.6.1.4.1.10106.3.101291.1.1.23
		gps3002c04v1SatNoFail OBJECT-TYPE
			SYNTAX BitFail
			MAX-ACCESS read-only
			STATUS current
			DESCRIPTION
				"Indicates that the number of visible satellites is low"
		::= { gps3002c04v1Entry 23 }

		-- 1.3.6.1.4.1.10106.3.101291.1.1.25
		gps3002c04v1GpsSiteSurv OBJECT-TYPE
			SYNTAX Bit0No1Yes
			MAX-ACCESS read-only
			STATUS current
			DESCRIPTION
				"Indicates that GPS receiver module is in site survey mode"
		::= { gps3002c04v1Entry 25 }

		-- 1.3.6.1.4.1.10106.3.101291.1.1.27
		gps3002c04v1GpsTrackSats OBJECT-TYPE
			SYNTAX GpsSatellites
			MAX-ACCESS read-only
			STATUS current
			DESCRIPTION
				"Number of GPS tracking satellites"
		::= { gps3002c04v1Entry 27 }

		-- 1.3.6.1.4.1.10106.3.101291.1.1.29
		gps3002c04v1GpsVisibleSats OBJECT-TYPE
			SYNTAX GpsSatellites
			MAX-ACCESS read-only
			STATUS current
			DESCRIPTION
				"Number of GPS visible satellites"
		::= { gps3002c04v1Entry 29 }

		-- 1.3.6.1.4.1.10106.3.101291.1.1.31
		gps3002c04v1GpsSignalLevel OBJECT-TYPE
			SYNTAX LevelDbHz
			MAX-ACCESS read-only
			STATUS current
			DESCRIPTION
				"Estimated carrier to noise ratio for the best satellite in tracking"
		::= { gps3002c04v1Entry 31 }

		-- 1.3.6.1.4.1.10106.3.101291.1.1.33
		gps3002c04v1HoldoverTime OBJECT-TYPE
			SYNTAX GpsHoldovrTime
			MAX-ACCESS read-only
			STATUS current
			DESCRIPTION
				"Holdover time"
		::= { gps3002c04v1Entry 33 }

		-- 1.3.6.1.4.1.10106.3.101291.1.1.35
		gps3002c04v1FreqDriftEst OBJECT-TYPE
			SYNTAX GpsFrqDrftEst
			MAX-ACCESS read-only
			STATUS current
			DESCRIPTION
				"Frequency drift estimation"
		::= { gps3002c04v1Entry 35 }

		-- 1.3.6.1.4.1.10106.3.101291.1.1.37
		gps3002c04v1PhaseDriftEst OBJECT-TYPE
			SYNTAX GpsPhsDrftEst
			MAX-ACCESS read-only
			STATUS current
			DESCRIPTION
				"Phase drift estimation"
		::= { gps3002c04v1Entry 37 }

		-- 1.3.6.1.4.1.10106.3.101291.1.1.39
		gps3002c04v1SerialNo OBJECT-TYPE
			SYNTAX SerialNo
			MAX-ACCESS read-only
			STATUS current
			DESCRIPTION
				"Serial number"
		::= { gps3002c04v1Entry 39 }

		-- 1.3.6.1.4.1.10106.3.443601
		cws2016c01v1 OBJECT IDENTIFIER ::= { albalaProducts 443601 }

		-- 1.3.6.1.4.1.10106.3.443601.1
		cws2016c01v1Table  OBJECT-TYPE
			SYNTAX SEQUENCE OF Cws2016c01v1Entry
			MAX-ACCESS not-accessible
			STATUS current
			DESCRIPTION
				"Module  CWS2016C01V1 Table"
			::= { cws2016c01v1 1 }

		-- 1.3.6.1.4.1.10106.3.443601.1.1
		cws2016c01v1Entry  OBJECT-TYPE
			SYNTAX Cws2016c01v1Entry
			MAX-ACCESS not-accessible
			STATUS current
			DESCRIPTION
				"Module CWS2016C01V1 Entry"
			INDEX { cws2016c01v1Index }
			::= { cws2016c01v1Table 1 }

			Cws2016c01v1Entry ::=
			SEQUENCE {
				cws2016c01v1Index
				ModuleIndex,
				cws2016c01v1SerialNo
				SerialNo
			 }

		-- 1.3.6.1.4.1.10106.3.101291.1.1.1
		cws2016c01v1Index OBJECT-TYPE
			SYNTAX ModuleIndex
			MAX-ACCESS read-only
			STATUS current
			DESCRIPTION
				"Index of CWS2016C01V1 Table"
		::= { cws2016c01v1Entry 1 }

		-- 1.3.6.1.4.1.10106.3.101291.1.1.3
		cws2016c01v1SerialNo OBJECT-TYPE
			SYNTAX SerialNo
			MAX-ACCESS read-only
			STATUS current
			DESCRIPTION
				"Serial number"
		::= { cws2016c01v1Entry 3 }

		-- 1.3.6.1.4.1.10106.3.445101
		hdc2000c02v1 OBJECT IDENTIFIER ::= { albalaProducts 445101 }

		-- 1.3.6.1.4.1.10106.3.445101.1
		hdc2000c02v1Table  OBJECT-TYPE
			SYNTAX SEQUENCE OF Hdc2000c02v1Entry
			MAX-ACCESS not-accessible
			STATUS current
			DESCRIPTION
				"Module  HDC2000C02V1 Table"
			::= { hdc2000c02v1 1 }

		-- 1.3.6.1.4.1.10106.3.445101.1.1
		hdc2000c02v1Entry  OBJECT-TYPE
			SYNTAX Hdc2000c02v1Entry
			MAX-ACCESS not-accessible
			STATUS current
			DESCRIPTION
				"Module HDC2000C02V1 Entry"
			INDEX { hdc2000c02v1Index }
			::= { hdc2000c02v1Table 1 }

			Hdc2000c02v1Entry ::=
			SEQUENCE {
				hdc2000c02v1Index
				ModuleIndex,
				hdc2000c02v1ActivePreset
				Preset16Active,
				hdc2000c02v1LoadPreset
				Preset16Load,
				hdc2000c02v1SavePreset
				Preset16Save,
				hdc2000c02v1AnaRefFmt
				SdiHd3gFmt5,
				hdc2000c02v1AnaRefFmtTrapEnable
				AlarmEnable,
				hdc2000c02v1GenlockMode
				GenlockM0de2,
				hdc2000c02v1EnaAud20Bit
				Bit0No1Yes,
				hdc2000c02v1ModeConv
				Bit0Aut1Man,
				hdc2000c02v1ModeConvTrapEnable
				AlarmEnable,
				hdc2000c02v1OutAfd
				Afd1,
				hdc2000c02v1OutAfdTrapEnable
				AlarmEnable,
				hdc2000c02v1OutCf
				Cf1,
				hdc2000c02v1OutCfTrapEnable
				AlarmEnable,
				hdc2000c02v1InAfdExpct
				Afd1,
				hdc2000c02v1InAfdExpctTrapEnable
				AlarmEnable,
				hdc2000c02v1InCfExpct
				Cf1,
				hdc2000c02v1InCfExpctTrapEnable
				AlarmEnable,
				hdc2000c02v1OutsdEnaS2016
				Bit0No1Yes,
				hdc2000c02v1OutsdEnaVii
				Bit0No1Yes,
				hdc2000c02v1OutsdEnaWss
				Bit0No1Yes,
				hdc2000c02v1OutsdEnaVitc
				Bit0No1Yes,
				hdc2000c02v1OutsdEnaTxt
				Bit0No1Yes,
				hdc2000c02v1SelAudPair0
				AudioMxInput5,
				hdc2000c02v1SelAudPair1
				AudioMxInput5,
				hdc2000c02v1SelAudPair2
				AudioMxInput5,
				hdc2000c02v1SelAudPair3
				AudioMxInput5,
				hdc2000c02v1SelAudPair4
				AudioMxInput5,
				hdc2000c02v1SelAudPair5
				AudioMxInput5,
				hdc2000c02v1SelAudPair6
				AudioMxInput5,
				hdc2000c02v1SelAudPair7
				AudioMxInput5,
				hdc2000c02v1ChromaDis
				Bit0Ena1Dis,
				hdc2000c02v1LumaFilter
				Uint2,
				hdc2000c02v1VbiBlank
				Bit0Pas1Bnk,
				hdc2000c02v1VDelaySd
				DelayLines2,
				hdc2000c02v1HDelaySd
				DelayPixel5,
				hdc2000c02v1Grp1P0Gain
				Gain24dbMute,
				hdc2000c02v1Grp1P0Phase
				Bit0Nor1Inv,
				hdc2000c02v1Grp1P1Gain
				Gain24dbMute,
				hdc2000c02v1Grp1P1Phase
				Bit0Nor1Inv,
				hdc2000c02v1Grp2P0Gain
				Gain24dbMute,
				hdc2000c02v1Grp2P0Phase
				Bit0Nor1Inv,
				hdc2000c02v1Grp2P1Gain
				Gain24dbMute,
				hdc2000c02v1Grp2P1Phase
				Bit0Nor1Inv,
				hdc2000c02v1Grp3P0Gain
				Gain24dbMute,
				hdc2000c02v1Grp3P0Phase
				Bit0Nor1Inv,
				hdc2000c02v1Grp3P1Gain
				Gain24dbMute,
				hdc2000c02v1Grp3P1Phase
				Bit0Nor1Inv,
				hdc2000c02v1Grp4P0Gain
				Gain24dbMute,
				hdc2000c02v1Grp4P0Phase
				Bit0Nor1Inv,
				hdc2000c02v1Grp4P1Gain
				Gain24dbMute,
				hdc2000c02v1Grp4P1Phase
				Bit0Nor1Inv,
				hdc2000c02v1InAfdDetct
				Afd1,
				hdc2000c02v1InAfdDetctTrapEnable
				AlarmEnable,
				hdc2000c02v1InCfDetct
				Cf1,
				hdc2000c02v1InCfDetctTrapEnable
				AlarmEnable,
				hdc2000c02v1InPhyFail
				BitFail,
				hdc2000c02v1InPhyFailTrapEnable
				AlarmEnable,
				hdc2000c02v1InFmtFail
				BitFail,
				hdc2000c02v1InFmtFailTrapEnable
				AlarmEnable,
				hdc2000c02v1InIncFail
				BitFail,
				hdc2000c02v1InIncFailTrapEnable
				AlarmEnable,
				hdc2000c02v1InPresCrcFail
				BitFail,
				hdc2000c02v1InCrcFail
				BitFail,
				hdc2000c02v1InCrcFailTrapEnable
				AlarmEnable,
				hdc2000c02v1InPrsS352Fail
				BitFail,
				hdc2000c02v1InS352Fail
				BitFail,
				hdc2000c02v1PresS2016Fail
				BitFail,
				hdc2000c02v1ErrS2016Fail
				BitFail,
				hdc2000c02v1PresAudG1Fail
				BitFail,
				hdc2000c02v1PresAudG1FailTrapEnable
				AlarmEnable,
				hdc2000c02v1PresAudG2Fail
				BitFail,
				hdc2000c02v1PresAudG2FailTrapEnable
				AlarmEnable,
				hdc2000c02v1PresAudG3Fail
				BitFail,
				hdc2000c02v1PresAudG3FailTrapEnable
				AlarmEnable,
				hdc2000c02v1PresAudG4Fail
				BitFail,
				hdc2000c02v1PresAudG4FailTrapEnable
				AlarmEnable,
				hdc2000c02v1RefFail
				BitFail,
				hdc2000c02v1RefFailTrapEnable
				AlarmEnable,
				hdc2000c02v1RefFmtFail
				BitFail,
				hdc2000c02v1RefFmtFailTrapEnable
				AlarmEnable,
				hdc2000c02v1LockFail
				BitFail,
				hdc2000c02v1LockFailTrapEnable
				AlarmEnable,
				hdc2000c02v1AudPair0Fail
				BitFail,
				hdc2000c02v1AudPair0FailTrapEnable
				AlarmEnable,
				hdc2000c02v1AudPair1Fail
				BitFail,
				hdc2000c02v1AudPair1FailTrapEnable
				AlarmEnable,
				hdc2000c02v1AudPair2Fail
				BitFail,
				hdc2000c02v1AudPair2FailTrapEnable
				AlarmEnable,
				hdc2000c02v1AudPair3Fail
				BitFail,
				hdc2000c02v1AudPair3FailTrapEnable
				AlarmEnable,
				hdc2000c02v1AudPair4Fail
				BitFail,
				hdc2000c02v1AudPair4FailTrapEnable
				AlarmEnable,
				hdc2000c02v1AudPair5Fail
				BitFail,
				hdc2000c02v1AudPair5FailTrapEnable
				AlarmEnable,
				hdc2000c02v1AudPair6Fail
				BitFail,
				hdc2000c02v1AudPair6FailTrapEnable
				AlarmEnable,
				hdc2000c02v1AudPair7Fail
				BitFail,
				hdc2000c02v1AudPair7FailTrapEnable
				AlarmEnable,
				hdc2000c02v1InFormat
				SdiHd3gFmt3,
				hdc2000c02v1InFormatTrapEnable
				AlarmEnable,
				hdc2000c02v1RefFormat
				SdiHd3gFmt3,
				hdc2000c02v1RefFormatTrapEnable
				AlarmEnable,
				hdc2000c02v1MuteSd
				Bit0No1Yes,
				hdc2000c02v1BlackSd
				Bit0No1Yes,
				hdc2000c02v1SerialNo
				SerialNo,
				hdc2000c02v1OutsdEnaCea608
				Bit0No1Yes
			 }

		-- 1.3.6.1.4.1.10106.3.101291.1.1.1
		hdc2000c02v1Index OBJECT-TYPE
			SYNTAX ModuleIndex
			MAX-ACCESS read-only
			STATUS current
			DESCRIPTION
				"Index of HDC2000C02V1 Table"
		::= { hdc2000c02v1Entry 1 }

		-- 1.3.6.1.4.1.10106.3.101291.1.1.3
		hdc2000c02v1ActivePreset OBJECT-TYPE
			SYNTAX Preset16Active
			MAX-ACCESS read-only
			STATUS current
			DESCRIPTION
				"Shows the active preset"
		::= { hdc2000c02v1Entry 3 }

		-- 1.3.6.1.4.1.10106.3.101291.1.1.5
		hdc2000c02v1LoadPreset OBJECT-TYPE
			SYNTAX Preset16Load
			MAX-ACCESS read-write
			STATUS current
			DESCRIPTION
				"Allows loading a preset"
		::= { hdc2000c02v1Entry 5 }

		-- 1.3.6.1.4.1.10106.3.101291.1.1.7
		hdc2000c02v1SavePreset OBJECT-TYPE
			SYNTAX Preset16Save
			MAX-ACCESS read-write
			STATUS current
			DESCRIPTION
				"Allows saving a preset"
		::= { hdc2000c02v1Entry 7 }

		-- 1.3.6.1.4.1.10106.3.101291.1.1.9
		hdc2000c02v1AnaRefFmt OBJECT-TYPE
			SYNTAX SdiHd3gFmt5
			MAX-ACCESS read-write
			STATUS current
			DESCRIPTION
				"Analog reference input format"
		::= { hdc2000c02v1Entry 9 }

		-- 1.3.6.1.4.1.10106.3.101291.1.1.10
		hdc2000c02v1AnaRefFmtTrapEnable OBJECT-TYPE
			SYNTAX AlarmEnable
			MAX-ACCESS read-write
			STATUS current
			DESCRIPTION
				"Analog reference input format Trap Enable"
		::= { hdc2000c02v1Entry 10 }

		-- 1.3.6.1.4.1.10106.3.101291.1.1.11
		hdc2000c02v1GenlockMode OBJECT-TYPE
			SYNTAX GenlockM0de2
			MAX-ACCESS read-write
			STATUS current
			DESCRIPTION
				"Allos selecting the reference input signal"
		::= { hdc2000c02v1Entry 11 }

		-- 1.3.6.1.4.1.10106.3.101291.1.1.13
		hdc2000c02v1EnaAud20Bit OBJECT-TYPE
			SYNTAX Bit0No1Yes
			MAX-ACCESS read-write
			STATUS current
			DESCRIPTION
				"Enable 20-bit audio instead of 24-bit"
		::= { hdc2000c02v1Entry 13 }

		-- 1.3.6.1.4.1.10106.3.101291.1.1.15
		hdc2000c02v1ModeConv OBJECT-TYPE
			SYNTAX Bit0Aut1Man
			MAX-ACCESS read-write
			STATUS current
			DESCRIPTION
				"Conversion mode"
		::= { hdc2000c02v1Entry 15 }

		-- 1.3.6.1.4.1.10106.3.101291.1.1.16
		hdc2000c02v1ModeConvTrapEnable OBJECT-TYPE
			SYNTAX AlarmEnable
			MAX-ACCESS read-write
			STATUS current
			DESCRIPTION
				"Conversion mode Trap Enable"
		::= { hdc2000c02v1Entry 16 }

		-- 1.3.6.1.4.1.10106.3.101291.1.1.17
		hdc2000c02v1OutAfd OBJECT-TYPE
			SYNTAX Afd1
			MAX-ACCESS read-write
			STATUS current
			DESCRIPTION
				"Output active format description"
		::= { hdc2000c02v1Entry 17 }

		-- 1.3.6.1.4.1.10106.3.101291.1.1.18
		hdc2000c02v1OutAfdTrapEnable OBJECT-TYPE
			SYNTAX AlarmEnable
			MAX-ACCESS read-write
			STATUS current
			DESCRIPTION
				"Output active format description Trap Enable"
		::= { hdc2000c02v1Entry 18 }

		-- 1.3.6.1.4.1.10106.3.101291.1.1.19
		hdc2000c02v1OutCf OBJECT-TYPE
			SYNTAX Cf1
			MAX-ACCESS read-write
			STATUS current
			DESCRIPTION
				"Output coded frame"
		::= { hdc2000c02v1Entry 19 }

		-- 1.3.6.1.4.1.10106.3.101291.1.1.20
		hdc2000c02v1OutCfTrapEnable OBJECT-TYPE
			SYNTAX AlarmEnable
			MAX-ACCESS read-write
			STATUS current
			DESCRIPTION
				"Output coded frame Trap Enable"
		::= { hdc2000c02v1Entry 20 }

		-- 1.3.6.1.4.1.10106.3.101291.1.1.21
		hdc2000c02v1InAfdExpct OBJECT-TYPE
			SYNTAX Afd1
			MAX-ACCESS read-write
			STATUS current
			DESCRIPTION
				"Input expected active format description"
		::= { hdc2000c02v1Entry 21 }

		-- 1.3.6.1.4.1.10106.3.101291.1.1.22
		hdc2000c02v1InAfdExpctTrapEnable OBJECT-TYPE
			SYNTAX AlarmEnable
			MAX-ACCESS read-write
			STATUS current
			DESCRIPTION
				"Input expected active format description Trap Enable"
		::= { hdc2000c02v1Entry 22 }

		-- 1.3.6.1.4.1.10106.3.101291.1.1.23
		hdc2000c02v1InCfExpct OBJECT-TYPE
			SYNTAX Cf1
			MAX-ACCESS read-write
			STATUS current
			DESCRIPTION
				"Input expected coded frame"
		::= { hdc2000c02v1Entry 23 }

		-- 1.3.6.1.4.1.10106.3.101291.1.1.24
		hdc2000c02v1InCfExpctTrapEnable OBJECT-TYPE
			SYNTAX AlarmEnable
			MAX-ACCESS read-write
			STATUS current
			DESCRIPTION
				"Input expected coded frame Trap Enable"
		::= { hdc2000c02v1Entry 24 }

		-- 1.3.6.1.4.1.10106.3.101291.1.1.25
		hdc2000c02v1OutsdEnaS2016 OBJECT-TYPE
			SYNTAX Bit0No1Yes
			MAX-ACCESS read-write
			STATUS current
			DESCRIPTION
				"Enables insertion of SMPTE 2016 packets in  OUTSD"
		::= { hdc2000c02v1Entry 25 }

		-- 1.3.6.1.4.1.10106.3.101291.1.1.27
		hdc2000c02v1OutsdEnaVii OBJECT-TYPE
			SYNTAX Bit0No1Yes
			MAX-ACCESS read-write
			STATUS current
			DESCRIPTION
				"Enables insertion of VII in OUTSD"
		::= { hdc2000c02v1Entry 27 }

		-- 1.3.6.1.4.1.10106.3.101291.1.1.29
		hdc2000c02v1OutsdEnaWss OBJECT-TYPE
			SYNTAX Bit0No1Yes
			MAX-ACCESS read-write
			STATUS current
			DESCRIPTION
				"Enables insertion of WSS in OUTSD"
		::= { hdc2000c02v1Entry 29 }

		-- 1.3.6.1.4.1.10106.3.101291.1.1.31
		hdc2000c02v1OutsdEnaVitc OBJECT-TYPE
			SYNTAX Bit0No1Yes
			MAX-ACCESS read-write
			STATUS current
			DESCRIPTION
				"Enables insertion of VITC in OUTSD"
		::= { hdc2000c02v1Entry 31 }

		-- 1.3.6.1.4.1.10106.3.101291.1.1.33
		hdc2000c02v1OutsdEnaTxt OBJECT-TYPE
			SYNTAX Bit0No1Yes
			MAX-ACCESS read-write
			STATUS current
			DESCRIPTION
				"Enables insertion of TXT in OUTSD"
		::= { hdc2000c02v1Entry 33 }

		-- 1.3.6.1.4.1.10106.3.101291.1.1.35
		hdc2000c02v1SelAudPair0 OBJECT-TYPE
			SYNTAX AudioMxInput5
			MAX-ACCESS read-write
			STATUS current
			DESCRIPTION
				"Selection of output audio for pair 0"
		::= { hdc2000c02v1Entry 35 }

		-- 1.3.6.1.4.1.10106.3.101291.1.1.37
		hdc2000c02v1SelAudPair1 OBJECT-TYPE
			SYNTAX AudioMxInput5
			MAX-ACCESS read-write
			STATUS current
			DESCRIPTION
				"Selection of output audio for pair 1"
		::= { hdc2000c02v1Entry 37 }

		-- 1.3.6.1.4.1.10106.3.101291.1.1.39
		hdc2000c02v1SelAudPair2 OBJECT-TYPE
			SYNTAX AudioMxInput5
			MAX-ACCESS read-write
			STATUS current
			DESCRIPTION
				"Selection of output audio for pair 2"
		::= { hdc2000c02v1Entry 39 }

		-- 1.3.6.1.4.1.10106.3.101291.1.1.41
		hdc2000c02v1SelAudPair3 OBJECT-TYPE
			SYNTAX AudioMxInput5
			MAX-ACCESS read-write
			STATUS current
			DESCRIPTION
				"Selection of output audio for pair 3"
		::= { hdc2000c02v1Entry 41 }

		-- 1.3.6.1.4.1.10106.3.101291.1.1.43
		hdc2000c02v1SelAudPair4 OBJECT-TYPE
			SYNTAX AudioMxInput5
			MAX-ACCESS read-write
			STATUS current
			DESCRIPTION
				"Selection of output audio for pair 4"
		::= { hdc2000c02v1Entry 43 }

		-- 1.3.6.1.4.1.10106.3.101291.1.1.45
		hdc2000c02v1SelAudPair5 OBJECT-TYPE
			SYNTAX AudioMxInput5
			MAX-ACCESS read-write
			STATUS current
			DESCRIPTION
				"Selection of output audio for pair 5"
		::= { hdc2000c02v1Entry 45 }

		-- 1.3.6.1.4.1.10106.3.101291.1.1.47
		hdc2000c02v1SelAudPair6 OBJECT-TYPE
			SYNTAX AudioMxInput5
			MAX-ACCESS read-write
			STATUS current
			DESCRIPTION
				"Selection of output audio for pair 6"
		::= { hdc2000c02v1Entry 47 }

		-- 1.3.6.1.4.1.10106.3.101291.1.1.49
		hdc2000c02v1SelAudPair7 OBJECT-TYPE
			SYNTAX AudioMxInput5
			MAX-ACCESS read-write
			STATUS current
			DESCRIPTION
				"Selection of output audio for pair 7"
		::= { hdc2000c02v1Entry 49 }

		-- 1.3.6.1.4.1.10106.3.101291.1.1.51
		hdc2000c02v1ChromaDis OBJECT-TYPE
			SYNTAX Bit0Ena1Dis
			MAX-ACCESS read-write
			STATUS current
			DESCRIPTION
				"Allows disabling chroma"
		::= { hdc2000c02v1Entry 51 }

		-- 1.3.6.1.4.1.10106.3.101291.1.1.53
		hdc2000c02v1LumaFilter OBJECT-TYPE
			SYNTAX Uint2
			MAX-ACCESS read-write
			STATUS current
			DESCRIPTION
				"Allows selecting luminance filter"
		::= { hdc2000c02v1Entry 53 }

		-- 1.3.6.1.4.1.10106.3.101291.1.1.55
		hdc2000c02v1VbiBlank OBJECT-TYPE
			SYNTAX Bit0Pas1Bnk
			MAX-ACCESS read-write
			STATUS current
			DESCRIPTION
				"Allows selecting if the VBI is blanked"
		::= { hdc2000c02v1Entry 55 }

		-- 1.3.6.1.4.1.10106.3.101291.1.1.57
		hdc2000c02v1VDelaySd OBJECT-TYPE
			SYNTAX DelayLines2
			MAX-ACCESS read-write
			STATUS current
			DESCRIPTION
				"Allows adjusting the SD downconverted video vertical delay"
		::= { hdc2000c02v1Entry 57 }

		-- 1.3.6.1.4.1.10106.3.101291.1.1.59
		hdc2000c02v1HDelaySd OBJECT-TYPE
			SYNTAX DelayPixel5
			MAX-ACCESS read-write
			STATUS current
			DESCRIPTION
				"Allows adjusting the SD downconverted video horizontal delay"
		::= { hdc2000c02v1Entry 59 }

		-- 1.3.6.1.4.1.10106.3.101291.1.1.61
		hdc2000c02v1Grp1P0Gain OBJECT-TYPE
			SYNTAX Gain24dbMute
			MAX-ACCESS read-write
			STATUS current
			DESCRIPTION
				"Group 1 pair 0 gain"
		::= { hdc2000c02v1Entry 61 }

		-- 1.3.6.1.4.1.10106.3.101291.1.1.63
		hdc2000c02v1Grp1P0Phase OBJECT-TYPE
			SYNTAX Bit0Nor1Inv
			MAX-ACCESS read-write
			STATUS current
			DESCRIPTION
				"Group 1 pair 0 phase"
		::= { hdc2000c02v1Entry 63 }

		-- 1.3.6.1.4.1.10106.3.101291.1.1.65
		hdc2000c02v1Grp1P1Gain OBJECT-TYPE
			SYNTAX Gain24dbMute
			MAX-ACCESS read-write
			STATUS current
			DESCRIPTION
				"Group 1 pair 1 gain"
		::= { hdc2000c02v1Entry 65 }

		-- 1.3.6.1.4.1.10106.3.101291.1.1.67
		hdc2000c02v1Grp1P1Phase OBJECT-TYPE
			SYNTAX Bit0Nor1Inv
			MAX-ACCESS read-write
			STATUS current
			DESCRIPTION
				"Group 1 pair 1 phase"
		::= { hdc2000c02v1Entry 67 }

		-- 1.3.6.1.4.1.10106.3.101291.1.1.69
		hdc2000c02v1Grp2P0Gain OBJECT-TYPE
			SYNTAX Gain24dbMute
			MAX-ACCESS read-write
			STATUS current
			DESCRIPTION
				"Group 2 pair 0 gain"
		::= { hdc2000c02v1Entry 69 }

		-- 1.3.6.1.4.1.10106.3.101291.1.1.71
		hdc2000c02v1Grp2P0Phase OBJECT-TYPE
			SYNTAX Bit0Nor1Inv
			MAX-ACCESS read-write
			STATUS current
			DESCRIPTION
				"Group 2 pair 0 phase"
		::= { hdc2000c02v1Entry 71 }

		-- 1.3.6.1.4.1.10106.3.101291.1.1.73
		hdc2000c02v1Grp2P1Gain OBJECT-TYPE
			SYNTAX Gain24dbMute
			MAX-ACCESS read-write
			STATUS current
			DESCRIPTION
				"Group 2 pair 1 gain"
		::= { hdc2000c02v1Entry 73 }

		-- 1.3.6.1.4.1.10106.3.101291.1.1.75
		hdc2000c02v1Grp2P1Phase OBJECT-TYPE
			SYNTAX Bit0Nor1Inv
			MAX-ACCESS read-write
			STATUS current
			DESCRIPTION
				"Group 2 pair 1 phase"
		::= { hdc2000c02v1Entry 75 }

		-- 1.3.6.1.4.1.10106.3.101291.1.1.77
		hdc2000c02v1Grp3P0Gain OBJECT-TYPE
			SYNTAX Gain24dbMute
			MAX-ACCESS read-write
			STATUS current
			DESCRIPTION
				"Group 3 pair 0 gain"
		::= { hdc2000c02v1Entry 77 }

		-- 1.3.6.1.4.1.10106.3.101291.1.1.79
		hdc2000c02v1Grp3P0Phase OBJECT-TYPE
			SYNTAX Bit0Nor1Inv
			MAX-ACCESS read-write
			STATUS current
			DESCRIPTION
				"Group 3 pair 0 phase"
		::= { hdc2000c02v1Entry 79 }

		-- 1.3.6.1.4.1.10106.3.101291.1.1.81
		hdc2000c02v1Grp3P1Gain OBJECT-TYPE
			SYNTAX Gain24dbMute
			MAX-ACCESS read-write
			STATUS current
			DESCRIPTION
				"Group 3 pair 1 gain"
		::= { hdc2000c02v1Entry 81 }

		-- 1.3.6.1.4.1.10106.3.101291.1.1.83
		hdc2000c02v1Grp3P1Phase OBJECT-TYPE
			SYNTAX Bit0Nor1Inv
			MAX-ACCESS read-write
			STATUS current
			DESCRIPTION
				"Group 3 pair 1 phase"
		::= { hdc2000c02v1Entry 83 }

		-- 1.3.6.1.4.1.10106.3.101291.1.1.85
		hdc2000c02v1Grp4P0Gain OBJECT-TYPE
			SYNTAX Gain24dbMute
			MAX-ACCESS read-write
			STATUS current
			DESCRIPTION
				"Group 4 pair 0 gain"
		::= { hdc2000c02v1Entry 85 }

		-- 1.3.6.1.4.1.10106.3.101291.1.1.87
		hdc2000c02v1Grp4P0Phase OBJECT-TYPE
			SYNTAX Bit0Nor1Inv
			MAX-ACCESS read-write
			STATUS current
			DESCRIPTION
				"Group 4 pair 0 phase"
		::= { hdc2000c02v1Entry 87 }

		-- 1.3.6.1.4.1.10106.3.101291.1.1.89
		hdc2000c02v1Grp4P1Gain OBJECT-TYPE
			SYNTAX Gain24dbMute
			MAX-ACCESS read-write
			STATUS current
			DESCRIPTION
				"Group 4 pair 1 gain"
		::= { hdc2000c02v1Entry 89 }

		-- 1.3.6.1.4.1.10106.3.101291.1.1.91
		hdc2000c02v1Grp4P1Phase OBJECT-TYPE
			SYNTAX Bit0Nor1Inv
			MAX-ACCESS read-write
			STATUS current
			DESCRIPTION
				"Group 4 pair 1 phase"
		::= { hdc2000c02v1Entry 91 }

		-- 1.3.6.1.4.1.10106.3.101291.1.1.93
		hdc2000c02v1InAfdDetct OBJECT-TYPE
			SYNTAX Afd1
			MAX-ACCESS read-only
			STATUS current
			DESCRIPTION
				"Input detected AFD"
		::= { hdc2000c02v1Entry 93 }

		-- 1.3.6.1.4.1.10106.3.101291.1.1.94
		hdc2000c02v1InAfdDetctTrapEnable OBJECT-TYPE
			SYNTAX AlarmEnable
			MAX-ACCESS read-write
			STATUS current
			DESCRIPTION
				"Input detected AFD Trap Enable"
		::= { hdc2000c02v1Entry 94 }

		-- 1.3.6.1.4.1.10106.3.101291.1.1.95
		hdc2000c02v1InCfDetct OBJECT-TYPE
			SYNTAX Cf1
			MAX-ACCESS read-only
			STATUS current
			DESCRIPTION
				"Input detected coded frame"
		::= { hdc2000c02v1Entry 95 }

		-- 1.3.6.1.4.1.10106.3.101291.1.1.96
		hdc2000c02v1InCfDetctTrapEnable OBJECT-TYPE
			SYNTAX AlarmEnable
			MAX-ACCESS read-write
			STATUS current
			DESCRIPTION
				"Input detected coded frame Trap Enable"
		::= { hdc2000c02v1Entry 96 }

		-- 1.3.6.1.4.1.10106.3.101291.1.1.97
		hdc2000c02v1InPhyFail OBJECT-TYPE
			SYNTAX BitFail
			MAX-ACCESS read-only
			STATUS current
			DESCRIPTION
				"Absence fail"
		::= { hdc2000c02v1Entry 97 }

		-- 1.3.6.1.4.1.10106.3.101291.1.1.98
		hdc2000c02v1InPhyFailTrapEnable OBJECT-TYPE
			SYNTAX AlarmEnable
			MAX-ACCESS read-write
			STATUS current
			DESCRIPTION
				"Absence fail Trap Enable"
		::= { hdc2000c02v1Entry 98 }

		-- 1.3.6.1.4.1.10106.3.101291.1.1.99
		hdc2000c02v1InFmtFail OBJECT-TYPE
			SYNTAX BitFail
			MAX-ACCESS read-only
			STATUS current
			DESCRIPTION
				"Format fail"
		::= { hdc2000c02v1Entry 99 }

		-- 1.3.6.1.4.1.10106.3.101291.1.1.100
		hdc2000c02v1InFmtFailTrapEnable OBJECT-TYPE
			SYNTAX AlarmEnable
			MAX-ACCESS read-write
			STATUS current
			DESCRIPTION
				"Format fail Trap Enable"
		::= { hdc2000c02v1Entry 100 }

		-- 1.3.6.1.4.1.10106.3.101291.1.1.101
		hdc2000c02v1InIncFail OBJECT-TYPE
			SYNTAX BitFail
			MAX-ACCESS read-only
			STATUS current
			DESCRIPTION
				"Incompatible format fail"
		::= { hdc2000c02v1Entry 101 }

		-- 1.3.6.1.4.1.10106.3.101291.1.1.102
		hdc2000c02v1InIncFailTrapEnable OBJECT-TYPE
			SYNTAX AlarmEnable
			MAX-ACCESS read-write
			STATUS current
			DESCRIPTION
				"Incompatible format fail Trap Enable"
		::= { hdc2000c02v1Entry 102 }

		-- 1.3.6.1.4.1.10106.3.101291.1.1.103
		hdc2000c02v1InPresCrcFail OBJECT-TYPE
			SYNTAX BitFail
			MAX-ACCESS read-only
			STATUS current
			DESCRIPTION
				"EDH/CRC presence fail"
		::= { hdc2000c02v1Entry 103 }

		-- 1.3.6.1.4.1.10106.3.101291.1.1.105
		hdc2000c02v1InCrcFail OBJECT-TYPE
			SYNTAX BitFail
			MAX-ACCESS read-only
			STATUS current
			DESCRIPTION
				"EDH/CRC fail"
		::= { hdc2000c02v1Entry 105 }

		-- 1.3.6.1.4.1.10106.3.101291.1.1.106
		hdc2000c02v1InCrcFailTrapEnable OBJECT-TYPE
			SYNTAX AlarmEnable
			MAX-ACCESS read-write
			STATUS current
			DESCRIPTION
				"EDH/CRC fail Trap Enable"
		::= { hdc2000c02v1Entry 106 }

		-- 1.3.6.1.4.1.10106.3.101291.1.1.107
		hdc2000c02v1InPrsS352Fail OBJECT-TYPE
			SYNTAX BitFail
			MAX-ACCESS read-only
			STATUS current
			DESCRIPTION
				"SMPTE 352 presence fail"
		::= { hdc2000c02v1Entry 107 }

		-- 1.3.6.1.4.1.10106.3.101291.1.1.109
		hdc2000c02v1InS352Fail OBJECT-TYPE
			SYNTAX BitFail
			MAX-ACCESS read-only
			STATUS current
			DESCRIPTION
				"SMPTE 352 fail"
		::= { hdc2000c02v1Entry 109 }

		-- 1.3.6.1.4.1.10106.3.101291.1.1.111
		hdc2000c02v1PresS2016Fail OBJECT-TYPE
			SYNTAX BitFail
			MAX-ACCESS read-only
			STATUS current
			DESCRIPTION
				"SMPTE 2016 presence fail"
		::= { hdc2000c02v1Entry 111 }

		-- 1.3.6.1.4.1.10106.3.101291.1.1.113
		hdc2000c02v1ErrS2016Fail OBJECT-TYPE
			SYNTAX BitFail
			MAX-ACCESS read-only
			STATUS current
			DESCRIPTION
				"SMPTE 2016 error fail"
		::= { hdc2000c02v1Entry 113 }

		-- 1.3.6.1.4.1.10106.3.101291.1.1.115
		hdc2000c02v1PresAudG1Fail OBJECT-TYPE
			SYNTAX BitFail
			MAX-ACCESS read-only
			STATUS current
			DESCRIPTION
				"Audio group 1 presence fail"
		::= { hdc2000c02v1Entry 115 }

		-- 1.3.6.1.4.1.10106.3.101291.1.1.116
		hdc2000c02v1PresAudG1FailTrapEnable OBJECT-TYPE
			SYNTAX AlarmEnable
			MAX-ACCESS read-write
			STATUS current
			DESCRIPTION
				"Audio group 1 presence fail Trap Enable"
		::= { hdc2000c02v1Entry 116 }

		-- 1.3.6.1.4.1.10106.3.101291.1.1.117
		hdc2000c02v1PresAudG2Fail OBJECT-TYPE
			SYNTAX BitFail
			MAX-ACCESS read-only
			STATUS current
			DESCRIPTION
				"Audio group 2 presence fail"
		::= { hdc2000c02v1Entry 117 }

		-- 1.3.6.1.4.1.10106.3.101291.1.1.118
		hdc2000c02v1PresAudG2FailTrapEnable OBJECT-TYPE
			SYNTAX AlarmEnable
			MAX-ACCESS read-write
			STATUS current
			DESCRIPTION
				"Audio group 2 presence fail Trap Enable"
		::= { hdc2000c02v1Entry 118 }

		-- 1.3.6.1.4.1.10106.3.101291.1.1.119
		hdc2000c02v1PresAudG3Fail OBJECT-TYPE
			SYNTAX BitFail
			MAX-ACCESS read-only
			STATUS current
			DESCRIPTION
				"Audio group 3 presence fail"
		::= { hdc2000c02v1Entry 119 }

		-- 1.3.6.1.4.1.10106.3.101291.1.1.120
		hdc2000c02v1PresAudG3FailTrapEnable OBJECT-TYPE
			SYNTAX AlarmEnable
			MAX-ACCESS read-write
			STATUS current
			DESCRIPTION
				"Audio group 3 presence fail Trap Enable"
		::= { hdc2000c02v1Entry 120 }

		-- 1.3.6.1.4.1.10106.3.101291.1.1.121
		hdc2000c02v1PresAudG4Fail OBJECT-TYPE
			SYNTAX BitFail
			MAX-ACCESS read-only
			STATUS current
			DESCRIPTION
				"Audio group 4 presence fail"
		::= { hdc2000c02v1Entry 121 }

		-- 1.3.6.1.4.1.10106.3.101291.1.1.122
		hdc2000c02v1PresAudG4FailTrapEnable OBJECT-TYPE
			SYNTAX AlarmEnable
			MAX-ACCESS read-write
			STATUS current
			DESCRIPTION
				"Audio group 4 presence fail Trap Enable"
		::= { hdc2000c02v1Entry 122 }

		-- 1.3.6.1.4.1.10106.3.101291.1.1.123
		hdc2000c02v1RefFail OBJECT-TYPE
			SYNTAX BitFail
			MAX-ACCESS read-only
			STATUS current
			DESCRIPTION
				"Analog reference absence fail"
		::= { hdc2000c02v1Entry 123 }

		-- 1.3.6.1.4.1.10106.3.101291.1.1.124
		hdc2000c02v1RefFailTrapEnable OBJECT-TYPE
			SYNTAX AlarmEnable
			MAX-ACCESS read-write
			STATUS current
			DESCRIPTION
				"Analog reference absence fail Trap Enable"
		::= { hdc2000c02v1Entry 124 }

		-- 1.3.6.1.4.1.10106.3.101291.1.1.125
		hdc2000c02v1RefFmtFail OBJECT-TYPE
			SYNTAX BitFail
			MAX-ACCESS read-only
			STATUS current
			DESCRIPTION
				"Analog reference format fail"
		::= { hdc2000c02v1Entry 125 }

		-- 1.3.6.1.4.1.10106.3.101291.1.1.126
		hdc2000c02v1RefFmtFailTrapEnable OBJECT-TYPE
			SYNTAX AlarmEnable
			MAX-ACCESS read-write
			STATUS current
			DESCRIPTION
				"Analog reference format fail Trap Enable"
		::= { hdc2000c02v1Entry 126 }

		-- 1.3.6.1.4.1.10106.3.101291.1.1.127
		hdc2000c02v1LockFail OBJECT-TYPE
			SYNTAX BitFail
			MAX-ACCESS read-only
			STATUS current
			DESCRIPTION
				"Reference unlock fail"
		::= { hdc2000c02v1Entry 127 }

		-- 1.3.6.1.4.1.10106.3.101291.1.1.128
		hdc2000c02v1LockFailTrapEnable OBJECT-TYPE
			SYNTAX AlarmEnable
			MAX-ACCESS read-write
			STATUS current
			DESCRIPTION
				"Reference unlock fail Trap Enable"
		::= { hdc2000c02v1Entry 128 }

		-- 1.3.6.1.4.1.10106.3.101291.1.1.129
		hdc2000c02v1AudPair0Fail OBJECT-TYPE
			SYNTAX BitFail
			MAX-ACCESS read-only
			STATUS current
			DESCRIPTION
				"Audio pair 0 fail"
		::= { hdc2000c02v1Entry 129 }

		-- 1.3.6.1.4.1.10106.3.101291.1.1.130
		hdc2000c02v1AudPair0FailTrapEnable OBJECT-TYPE
			SYNTAX AlarmEnable
			MAX-ACCESS read-write
			STATUS current
			DESCRIPTION
				"Audio pair 0 fail Trap Enable"
		::= { hdc2000c02v1Entry 130 }

		-- 1.3.6.1.4.1.10106.3.101291.1.1.131
		hdc2000c02v1AudPair1Fail OBJECT-TYPE
			SYNTAX BitFail
			MAX-ACCESS read-only
			STATUS current
			DESCRIPTION
				"Audio pair 1 fail"
		::= { hdc2000c02v1Entry 131 }

		-- 1.3.6.1.4.1.10106.3.101291.1.1.132
		hdc2000c02v1AudPair1FailTrapEnable OBJECT-TYPE
			SYNTAX AlarmEnable
			MAX-ACCESS read-write
			STATUS current
			DESCRIPTION
				"Audio pair 1 fail Trap Enable"
		::= { hdc2000c02v1Entry 132 }

		-- 1.3.6.1.4.1.10106.3.101291.1.1.133
		hdc2000c02v1AudPair2Fail OBJECT-TYPE
			SYNTAX BitFail
			MAX-ACCESS read-only
			STATUS current
			DESCRIPTION
				"Audio pair 2 fail"
		::= { hdc2000c02v1Entry 133 }

		-- 1.3.6.1.4.1.10106.3.101291.1.1.134
		hdc2000c02v1AudPair2FailTrapEnable OBJECT-TYPE
			SYNTAX AlarmEnable
			MAX-ACCESS read-write
			STATUS current
			DESCRIPTION
				"Audio pair 2 fail Trap Enable"
		::= { hdc2000c02v1Entry 134 }

		-- 1.3.6.1.4.1.10106.3.101291.1.1.135
		hdc2000c02v1AudPair3Fail OBJECT-TYPE
			SYNTAX BitFail
			MAX-ACCESS read-only
			STATUS current
			DESCRIPTION
				"Audio pair 3 fail"
		::= { hdc2000c02v1Entry 135 }

		-- 1.3.6.1.4.1.10106.3.101291.1.1.136
		hdc2000c02v1AudPair3FailTrapEnable OBJECT-TYPE
			SYNTAX AlarmEnable
			MAX-ACCESS read-write
			STATUS current
			DESCRIPTION
				"Audio pair 3 fail Trap Enable"
		::= { hdc2000c02v1Entry 136 }

		-- 1.3.6.1.4.1.10106.3.101291.1.1.137
		hdc2000c02v1AudPair4Fail OBJECT-TYPE
			SYNTAX BitFail
			MAX-ACCESS read-only
			STATUS current
			DESCRIPTION
				"Audio pair 4 fail"
		::= { hdc2000c02v1Entry 137 }

		-- 1.3.6.1.4.1.10106.3.101291.1.1.138
		hdc2000c02v1AudPair4FailTrapEnable OBJECT-TYPE
			SYNTAX AlarmEnable
			MAX-ACCESS read-write
			STATUS current
			DESCRIPTION
				"Audio pair 4 fail Trap Enable"
		::= { hdc2000c02v1Entry 138 }

		-- 1.3.6.1.4.1.10106.3.101291.1.1.139
		hdc2000c02v1AudPair5Fail OBJECT-TYPE
			SYNTAX BitFail
			MAX-ACCESS read-only
			STATUS current
			DESCRIPTION
				"Audio pair 5 fail"
		::= { hdc2000c02v1Entry 139 }

		-- 1.3.6.1.4.1.10106.3.101291.1.1.140
		hdc2000c02v1AudPair5FailTrapEnable OBJECT-TYPE
			SYNTAX AlarmEnable
			MAX-ACCESS read-write
			STATUS current
			DESCRIPTION
				"Audio pair 5 fail Trap Enable"
		::= { hdc2000c02v1Entry 140 }

		-- 1.3.6.1.4.1.10106.3.101291.1.1.141
		hdc2000c02v1AudPair6Fail OBJECT-TYPE
			SYNTAX BitFail
			MAX-ACCESS read-only
			STATUS current
			DESCRIPTION
				"Audio pair 6 fail"
		::= { hdc2000c02v1Entry 141 }

		-- 1.3.6.1.4.1.10106.3.101291.1.1.142
		hdc2000c02v1AudPair6FailTrapEnable OBJECT-TYPE
			SYNTAX AlarmEnable
			MAX-ACCESS read-write
			STATUS current
			DESCRIPTION
				"Audio pair 6 fail Trap Enable"
		::= { hdc2000c02v1Entry 142 }

		-- 1.3.6.1.4.1.10106.3.101291.1.1.143
		hdc2000c02v1AudPair7Fail OBJECT-TYPE
			SYNTAX BitFail
			MAX-ACCESS read-only
			STATUS current
			DESCRIPTION
				"Audio pair 7 fail"
		::= { hdc2000c02v1Entry 143 }

		-- 1.3.6.1.4.1.10106.3.101291.1.1.144
		hdc2000c02v1AudPair7FailTrapEnable OBJECT-TYPE
			SYNTAX AlarmEnable
			MAX-ACCESS read-write
			STATUS current
			DESCRIPTION
				"Audio pair 7 fail Trap Enable"
		::= { hdc2000c02v1Entry 144 }

		-- 1.3.6.1.4.1.10106.3.101291.1.1.145
		hdc2000c02v1InFormat OBJECT-TYPE
			SYNTAX SdiHd3gFmt3
			MAX-ACCESS read-only
			STATUS current
			DESCRIPTION
				"Input format"
		::= { hdc2000c02v1Entry 145 }

		-- 1.3.6.1.4.1.10106.3.101291.1.1.146
		hdc2000c02v1InFormatTrapEnable OBJECT-TYPE
			SYNTAX AlarmEnable
			MAX-ACCESS read-write
			STATUS current
			DESCRIPTION
				"Input format Trap Enable"
		::= { hdc2000c02v1Entry 146 }

		-- 1.3.6.1.4.1.10106.3.101291.1.1.147
		hdc2000c02v1RefFormat OBJECT-TYPE
			SYNTAX SdiHd3gFmt3
			MAX-ACCESS read-only
			STATUS current
			DESCRIPTION
				"Reference format"
		::= { hdc2000c02v1Entry 147 }

		-- 1.3.6.1.4.1.10106.3.101291.1.1.148
		hdc2000c02v1RefFormatTrapEnable OBJECT-TYPE
			SYNTAX AlarmEnable
			MAX-ACCESS read-write
			STATUS current
			DESCRIPTION
				"Reference format Trap Enable"
		::= { hdc2000c02v1Entry 148 }

		-- 1.3.6.1.4.1.10106.3.101291.1.1.149
		hdc2000c02v1MuteSd OBJECT-TYPE
			SYNTAX Bit0No1Yes
			MAX-ACCESS read-only
			STATUS current
			DESCRIPTION
				"Muted SD output"
		::= { hdc2000c02v1Entry 149 }

		-- 1.3.6.1.4.1.10106.3.101291.1.1.151
		hdc2000c02v1BlackSd OBJECT-TYPE
			SYNTAX Bit0No1Yes
			MAX-ACCESS read-only
			STATUS current
			DESCRIPTION
				"Black SD output"
		::= { hdc2000c02v1Entry 151 }

		-- 1.3.6.1.4.1.10106.3.101291.1.1.153
		hdc2000c02v1SerialNo OBJECT-TYPE
			SYNTAX SerialNo
			MAX-ACCESS read-only
			STATUS current
			DESCRIPTION
				"Serial number"
		::= { hdc2000c02v1Entry 153 }

		-- 1.3.6.1.4.1.10106.3.101291.1.1.155
		hdc2000c02v1OutsdEnaCea608 OBJECT-TYPE
			SYNTAX Bit0No1Yes
			MAX-ACCESS read-write
			STATUS current
			DESCRIPTION
				"Enables insertion of CEA608 in OUTSD"
		::= { hdc2000c02v1Entry 155 }

		-- 1.3.6.1.4.1.10106.3.446901
		hxc3000c01v1 OBJECT IDENTIFIER ::= { albalaProducts 446901 }

		-- 1.3.6.1.4.1.10106.3.446901.1
		hxc3000c01v1Table  OBJECT-TYPE
			SYNTAX SEQUENCE OF Hxc3000c01v1Entry
			MAX-ACCESS not-accessible
			STATUS current
			DESCRIPTION
				"Module  HXC3000C01V1 Table"
			::= { hxc3000c01v1 1 }

		-- 1.3.6.1.4.1.10106.3.446901.1.1
		hxc3000c01v1Entry  OBJECT-TYPE
			SYNTAX Hxc3000c01v1Entry
			MAX-ACCESS not-accessible
			STATUS current
			DESCRIPTION
				"Module HXC3000C01V1 Entry"
			INDEX { hxc3000c01v1Index }
			::= { hxc3000c01v1Table 1 }

			Hxc3000c01v1Entry ::=
			SEQUENCE {
				hxc3000c01v1Index
				ModuleIndex,
				hxc3000c01v1ActivePreset
				Preset16Active,
				hxc3000c01v1LoadPreset
				Preset16Load,
				hxc3000c01v1SavePreset
				Preset16Save,
				hxc3000c01v1AnaRefFmt
				SdiHd3gFmt6,
				hxc3000c01v1AnaRefFmtTrapEnable
				AlarmEnable,
				hxc3000c01v1GenlockMode
				GenlockM0de2,
				hxc3000c01v1EnaAud20Bit
				Bit0Yes1No,
				hxc3000c01v1FailMode
				Bit0Fre1Blk,
				hxc3000c01v1ModeConv
				Bit0Aut1Man,
				hxc3000c01v1ModeConvTrapEnable
				AlarmEnable,
				hxc3000c01v1OutAfd
				Afd1,
				hxc3000c01v1OutAfdTrapEnable
				AlarmEnable,
				hxc3000c01v1OutCf
				Cf1,
				hxc3000c01v1OutCfTrapEnable
				AlarmEnable,
				hxc3000c01v1Esc11
				BitMask,
				hxc3000c01v1InAfdExpct
				Afd1,
				hxc3000c01v1InAfdExpctTrapEnable
				AlarmEnable,
				hxc3000c01v1InCfExpct
				Cf1,
				hxc3000c01v1InCfExpctTrapEnable
				AlarmEnable,
				hxc3000c01v1TxFmt
				SdiHd3gFmt6,
				hxc3000c01v1TxFmtTrapEnable
				AlarmEnable,
				hxc3000c01v1DeintAlgorithm
				DeintAlgorithm,
				hxc3000c01v1DeintAlgorithmTrapEnable
				AlarmEnable,
				hxc3000c01v1OutEnaS2016
				Bit0No1Yes,
				hxc3000c01v1OutEnaVii
				Bit0No1Yes,
				hxc3000c01v1OutEnaWss
				Bit0No1Yes,
				hxc3000c01v1OutEnaVitc
				Bit0No1Yes,
				hxc3000c01v1OutEnaAtc
				Bit0No1Yes,
				hxc3000c01v1OutEnaTxt
				Bit0No1Yes,
				hxc3000c01v1OutEnaCea608
				Bit0No1Yes,
				hxc3000c01v1SelAudPair0
				AudioMxInput5,
				hxc3000c01v1SelAudPair1
				AudioMxInput5,
				hxc3000c01v1SelAudPair2
				AudioMxInput5,
				hxc3000c01v1SelAudPair3
				AudioMxInput5,
				hxc3000c01v1SelAudPair4
				AudioMxInput5,
				hxc3000c01v1SelAudPair5
				AudioMxInput5,
				hxc3000c01v1SelAudPair6
				AudioMxInput5,
				hxc3000c01v1SelAudPair7
				AudioMxInput5,
				hxc3000c01v1VDelay
				DelayLines2,
				hxc3000c01v1HDelay
				DelayPixel5,
				hxc3000c01v1Grp1P0Gain
				Gain24dbMute,
				hxc3000c01v1Grp1P0Phase
				Bit0Nor1Inv,
				hxc3000c01v1Grp1P1Gain
				Gain24dbMute,
				hxc3000c01v1Grp1P1Phase
				Bit0Nor1Inv,
				hxc3000c01v1Grp2P0Gain
				Gain24dbMute,
				hxc3000c01v1Grp2P0Phase
				Bit0Nor1Inv,
				hxc3000c01v1Grp2P1Gain
				Gain24dbMute,
				hxc3000c01v1Grp2P1Phase
				Bit0Nor1Inv,
				hxc3000c01v1Grp3P0Gain
				Gain24dbMute,
				hxc3000c01v1Grp3P0Phase
				Bit0Nor1Inv,
				hxc3000c01v1Grp3P1Gain
				Gain24dbMute,
				hxc3000c01v1Grp3P1Phase
				Bit0Nor1Inv,
				hxc3000c01v1Grp4P0Gain
				Gain24dbMute,
				hxc3000c01v1Grp4P0Phase
				Bit0Nor1Inv,
				hxc3000c01v1Grp4P1Gain
				Gain24dbMute,
				hxc3000c01v1Grp4P1Phase
				Bit0Nor1Inv,
				hxc3000c01v1StatFlash
				BitFailN,
				hxc3000c01v1InPhyFail
				BitFail,
				hxc3000c01v1InPhyFailTrapEnable
				AlarmEnable,
				hxc3000c01v1InFmtFail
				BitFail,
				hxc3000c01v1InFmtFailTrapEnable
				AlarmEnable,
				hxc3000c01v1InIncFail
				BitFail,
				hxc3000c01v1InIncFailTrapEnable
				AlarmEnable,
				hxc3000c01v1InPresCrcFail
				BitFail,
				hxc3000c01v1InCrcFail
				BitFail,
				hxc3000c01v1InCrcFailTrapEnable
				AlarmEnable,
				hxc3000c01v1InPrsS352Fail
				BitFail,
				hxc3000c01v1InS352Fail
				BitFail,
				hxc3000c01v1PresS2016Fail
				BitFail,
				hxc3000c01v1ErrS2016Fail
				BitFail,
				hxc3000c01v1PresAudG1Fail
				BitFail,
				hxc3000c01v1PresAudG1FailTrapEnable
				AlarmEnable,
				hxc3000c01v1PresAudG2Fail
				BitFail,
				hxc3000c01v1PresAudG2FailTrapEnable
				AlarmEnable,
				hxc3000c01v1PresAudG3Fail
				BitFail,
				hxc3000c01v1PresAudG3FailTrapEnable
				AlarmEnable,
				hxc3000c01v1PresAudG4Fail
				BitFail,
				hxc3000c01v1PresAudG4FailTrapEnable
				AlarmEnable,
				hxc3000c01v1RefFail
				BitFail,
				hxc3000c01v1RefFailTrapEnable
				AlarmEnable,
				hxc3000c01v1RefFmtFail
				BitFail,
				hxc3000c01v1RefFmtFailTrapEnable
				AlarmEnable,
				hxc3000c01v1LockFail
				BitFail,
				hxc3000c01v1LockFailTrapEnable
				AlarmEnable,
				hxc3000c01v1AudPair0Fail
				BitFail,
				hxc3000c01v1AudPair0FailTrapEnable
				AlarmEnable,
				hxc3000c01v1AudPair1Fail
				BitFail,
				hxc3000c01v1AudPair1FailTrapEnable
				AlarmEnable,
				hxc3000c01v1AudPair2Fail
				BitFail,
				hxc3000c01v1AudPair2FailTrapEnable
				AlarmEnable,
				hxc3000c01v1AudPair3Fail
				BitFail,
				hxc3000c01v1AudPair3FailTrapEnable
				AlarmEnable,
				hxc3000c01v1AudPair4Fail
				BitFail,
				hxc3000c01v1AudPair4FailTrapEnable
				AlarmEnable,
				hxc3000c01v1AudPair5Fail
				BitFail,
				hxc3000c01v1AudPair5FailTrapEnable
				AlarmEnable,
				hxc3000c01v1AudPair6Fail
				BitFail,
				hxc3000c01v1AudPair6FailTrapEnable
				AlarmEnable,
				hxc3000c01v1AudPair7Fail
				BitFail,
				hxc3000c01v1AudPair7FailTrapEnable
				AlarmEnable,
				hxc3000c01v1InAfdDetct
				Afd1,
				hxc3000c01v1InAfdDetctTrapEnable
				AlarmEnable,
				hxc3000c01v1InCfDetct
				Cf1,
				hxc3000c01v1InCfDetctTrapEnable
				AlarmEnable,
				hxc3000c01v1InFormat
				SdiHd3gFmt3,
				hxc3000c01v1InFormatTrapEnable
				AlarmEnable,
				hxc3000c01v1RefFormat
				SdiHd3gFmt3,
				hxc3000c01v1RefFormatTrapEnable
				AlarmEnable,
				hxc3000c01v1TxFormat
				SdiHd3gFmt3,
				hxc3000c01v1TxFormatTrapEnable
				AlarmEnable,
				hxc3000c01v1TxtPres
				BitFailN,
				hxc3000c01v1VitcPres
				BitFailN,
				hxc3000c01v1Mute
				Bit0No1Yes,
				hxc3000c01v1Black
				Bit0No1Yes,
				hxc3000c01v1Gpi1
				Bit0Off1On,
				hxc3000c01v1Gpi2
				Bit0Off1On,
				hxc3000c01v1Gpi3
				Bit0Off1On,
				hxc3000c01v1Gpi4
				Bit0Off1On,
				hxc3000c01v1SerialNo
				SerialNo,
				hxc3000c01v1MuteEna
				Bit0No1Yes
			 }

		-- 1.3.6.1.4.1.10106.3.101291.1.1.1
		hxc3000c01v1Index OBJECT-TYPE
			SYNTAX ModuleIndex
			MAX-ACCESS read-only
			STATUS current
			DESCRIPTION
				"Index of HXC3000C01V1 Table"
		::= { hxc3000c01v1Entry 1 }

		-- 1.3.6.1.4.1.10106.3.101291.1.1.3
		hxc3000c01v1ActivePreset OBJECT-TYPE
			SYNTAX Preset16Active
			MAX-ACCESS read-only
			STATUS current
			DESCRIPTION
				"Shows the active preset"
		::= { hxc3000c01v1Entry 3 }

		-- 1.3.6.1.4.1.10106.3.101291.1.1.5
		hxc3000c01v1LoadPreset OBJECT-TYPE
			SYNTAX Preset16Load
			MAX-ACCESS read-write
			STATUS current
			DESCRIPTION
				"Allows loading a preset"
		::= { hxc3000c01v1Entry 5 }

		-- 1.3.6.1.4.1.10106.3.101291.1.1.7
		hxc3000c01v1SavePreset OBJECT-TYPE
			SYNTAX Preset16Save
			MAX-ACCESS read-write
			STATUS current
			DESCRIPTION
				"Allows saving a preset"
		::= { hxc3000c01v1Entry 7 }

		-- 1.3.6.1.4.1.10106.3.101291.1.1.9
		hxc3000c01v1AnaRefFmt OBJECT-TYPE
			SYNTAX SdiHd3gFmt6
			MAX-ACCESS read-write
			STATUS current
			DESCRIPTION
				"Analog reference input format"
		::= { hxc3000c01v1Entry 9 }

		-- 1.3.6.1.4.1.10106.3.101291.1.1.10
		hxc3000c01v1AnaRefFmtTrapEnable OBJECT-TYPE
			SYNTAX AlarmEnable
			MAX-ACCESS read-write
			STATUS current
			DESCRIPTION
				"Analog reference input format Trap Enable"
		::= { hxc3000c01v1Entry 10 }

		-- 1.3.6.1.4.1.10106.3.101291.1.1.11
		hxc3000c01v1GenlockMode OBJECT-TYPE
			SYNTAX GenlockM0de2
			MAX-ACCESS read-write
			STATUS current
			DESCRIPTION
				"Allos selecting the reference input signal"
		::= { hxc3000c01v1Entry 11 }

		-- 1.3.6.1.4.1.10106.3.101291.1.1.13
		hxc3000c01v1EnaAud20Bit OBJECT-TYPE
			SYNTAX Bit0Yes1No
			MAX-ACCESS read-write
			STATUS current
			DESCRIPTION
				"Allows embedding 24-bit audio in SD signals"
		::= { hxc3000c01v1Entry 13 }

		-- 1.3.6.1.4.1.10106.3.101291.1.1.15
		hxc3000c01v1FailMode OBJECT-TYPE
			SYNTAX Bit0Fre1Blk
			MAX-ACCESS read-write
			STATUS current
			DESCRIPTION
				"Allows selecting the output video signal if the input fails"
		::= { hxc3000c01v1Entry 15 }

		-- 1.3.6.1.4.1.10106.3.101291.1.1.17
		hxc3000c01v1ModeConv OBJECT-TYPE
			SYNTAX Bit0Aut1Man
			MAX-ACCESS read-write
			STATUS current
			DESCRIPTION
				"Conversion mode"
		::= { hxc3000c01v1Entry 17 }

		-- 1.3.6.1.4.1.10106.3.101291.1.1.18
		hxc3000c01v1ModeConvTrapEnable OBJECT-TYPE
			SYNTAX AlarmEnable
			MAX-ACCESS read-write
			STATUS current
			DESCRIPTION
				"Conversion mode Trap Enable"
		::= { hxc3000c01v1Entry 18 }

		-- 1.3.6.1.4.1.10106.3.101291.1.1.19
		hxc3000c01v1OutAfd OBJECT-TYPE
			SYNTAX Afd1
			MAX-ACCESS read-write
			STATUS current
			DESCRIPTION
				"Output active format description"
		::= { hxc3000c01v1Entry 19 }

		-- 1.3.6.1.4.1.10106.3.101291.1.1.20
		hxc3000c01v1OutAfdTrapEnable OBJECT-TYPE
			SYNTAX AlarmEnable
			MAX-ACCESS read-write
			STATUS current
			DESCRIPTION
				"Output active format description Trap Enable"
		::= { hxc3000c01v1Entry 20 }

		-- 1.3.6.1.4.1.10106.3.101291.1.1.21
		hxc3000c01v1OutCf OBJECT-TYPE
			SYNTAX Cf1
			MAX-ACCESS read-write
			STATUS current
			DESCRIPTION
				"Output coded frame"
		::= { hxc3000c01v1Entry 21 }

		-- 1.3.6.1.4.1.10106.3.101291.1.1.22
		hxc3000c01v1OutCfTrapEnable OBJECT-TYPE
			SYNTAX AlarmEnable
			MAX-ACCESS read-write
			STATUS current
			DESCRIPTION
				"Output coded frame Trap Enable"
		::= { hxc3000c01v1Entry 22 }

		-- 1.3.6.1.4.1.10106.3.101291.1.1.23
		hxc3000c01v1Esc11 OBJECT-TYPE
			SYNTAX BitMask
			MAX-ACCESS read-write
			STATUS current
			DESCRIPTION
				"Enables the 1 to 1 scaling rate"
		::= { hxc3000c01v1Entry 23 }

		-- 1.3.6.1.4.1.10106.3.101291.1.1.25
		hxc3000c01v1InAfdExpct OBJECT-TYPE
			SYNTAX Afd1
			MAX-ACCESS read-write
			STATUS current
			DESCRIPTION
				"Input expected active format description"
		::= { hxc3000c01v1Entry 25 }

		-- 1.3.6.1.4.1.10106.3.101291.1.1.26
		hxc3000c01v1InAfdExpctTrapEnable OBJECT-TYPE
			SYNTAX AlarmEnable
			MAX-ACCESS read-write
			STATUS current
			DESCRIPTION
				"Input expected active format description Trap Enable"
		::= { hxc3000c01v1Entry 26 }

		-- 1.3.6.1.4.1.10106.3.101291.1.1.27
		hxc3000c01v1InCfExpct OBJECT-TYPE
			SYNTAX Cf1
			MAX-ACCESS read-write
			STATUS current
			DESCRIPTION
				"Input expected coded frame"
		::= { hxc3000c01v1Entry 27 }

		-- 1.3.6.1.4.1.10106.3.101291.1.1.28
		hxc3000c01v1InCfExpctTrapEnable OBJECT-TYPE
			SYNTAX AlarmEnable
			MAX-ACCESS read-write
			STATUS current
			DESCRIPTION
				"Input expected coded frame Trap Enable"
		::= { hxc3000c01v1Entry 28 }

		-- 1.3.6.1.4.1.10106.3.101291.1.1.29
		hxc3000c01v1TxFmt OBJECT-TYPE
			SYNTAX SdiHd3gFmt6
			MAX-ACCESS read-write
			STATUS current
			DESCRIPTION
				"Output format"
		::= { hxc3000c01v1Entry 29 }

		-- 1.3.6.1.4.1.10106.3.101291.1.1.30
		hxc3000c01v1TxFmtTrapEnable OBJECT-TYPE
			SYNTAX AlarmEnable
			MAX-ACCESS read-write
			STATUS current
			DESCRIPTION
				"Output format Trap Enable"
		::= { hxc3000c01v1Entry 30 }

		-- 1.3.6.1.4.1.10106.3.101291.1.1.31
		hxc3000c01v1DeintAlgorithm OBJECT-TYPE
			SYNTAX DeintAlgorithm
			MAX-ACCESS read-write
			STATUS current
			DESCRIPTION
				"Allows selecting the de-interlacing algorithm"
		::= { hxc3000c01v1Entry 31 }

		-- 1.3.6.1.4.1.10106.3.101291.1.1.32
		hxc3000c01v1DeintAlgorithmTrapEnable OBJECT-TYPE
			SYNTAX AlarmEnable
			MAX-ACCESS read-write
			STATUS current
			DESCRIPTION
				"Allows selecting the de-interlacing algorithm Trap Enable"
		::= { hxc3000c01v1Entry 32 }

		-- 1.3.6.1.4.1.10106.3.101291.1.1.33
		hxc3000c01v1OutEnaS2016 OBJECT-TYPE
			SYNTAX Bit0No1Yes
			MAX-ACCESS read-write
			STATUS current
			DESCRIPTION
				"Enables insertion of SMPTE 2016 packets in  OUT"
		::= { hxc3000c01v1Entry 33 }

		-- 1.3.6.1.4.1.10106.3.101291.1.1.35
		hxc3000c01v1OutEnaVii OBJECT-TYPE
			SYNTAX Bit0No1Yes
			MAX-ACCESS read-write
			STATUS current
			DESCRIPTION
				"Enables insertion of VII in OUT"
		::= { hxc3000c01v1Entry 35 }

		-- 1.3.6.1.4.1.10106.3.101291.1.1.37
		hxc3000c01v1OutEnaWss OBJECT-TYPE
			SYNTAX Bit0No1Yes
			MAX-ACCESS read-write
			STATUS current
			DESCRIPTION
				"Enables insertion of WSS in OUT"
		::= { hxc3000c01v1Entry 37 }

		-- 1.3.6.1.4.1.10106.3.101291.1.1.39
		hxc3000c01v1OutEnaVitc OBJECT-TYPE
			SYNTAX Bit0No1Yes
			MAX-ACCESS read-write
			STATUS current
			DESCRIPTION
				"Enables insertion of DVITC in OUT"
		::= { hxc3000c01v1Entry 39 }

		-- 1.3.6.1.4.1.10106.3.101291.1.1.41
		hxc3000c01v1OutEnaAtc OBJECT-TYPE
			SYNTAX Bit0No1Yes
			MAX-ACCESS read-write
			STATUS current
			DESCRIPTION
				"Enables insertion of ATC in OUT"
		::= { hxc3000c01v1Entry 41 }

		-- 1.3.6.1.4.1.10106.3.101291.1.1.43
		hxc3000c01v1OutEnaTxt OBJECT-TYPE
			SYNTAX Bit0No1Yes
			MAX-ACCESS read-write
			STATUS current
			DESCRIPTION
				"Enables insertion of TXT in OUT"
		::= { hxc3000c01v1Entry 43 }

		-- 1.3.6.1.4.1.10106.3.101291.1.1.45
		hxc3000c01v1OutEnaCea608 OBJECT-TYPE
			SYNTAX Bit0No1Yes
			MAX-ACCESS read-write
			STATUS current
			DESCRIPTION
				"Enables insertion of CEA608 modulation in OUT when format is 486I59.94 and CEA608 or CEA708 paquets are present"
		::= { hxc3000c01v1Entry 45 }

		-- 1.3.6.1.4.1.10106.3.101291.1.1.47
		hxc3000c01v1SelAudPair0 OBJECT-TYPE
			SYNTAX AudioMxInput5
			MAX-ACCESS read-write
			STATUS current
			DESCRIPTION
				"Selection of output audio for pair 0"
		::= { hxc3000c01v1Entry 47 }

		-- 1.3.6.1.4.1.10106.3.101291.1.1.49
		hxc3000c01v1SelAudPair1 OBJECT-TYPE
			SYNTAX AudioMxInput5
			MAX-ACCESS read-write
			STATUS current
			DESCRIPTION
				"Selection of output audio for pair 1"
		::= { hxc3000c01v1Entry 49 }

		-- 1.3.6.1.4.1.10106.3.101291.1.1.51
		hxc3000c01v1SelAudPair2 OBJECT-TYPE
			SYNTAX AudioMxInput5
			MAX-ACCESS read-write
			STATUS current
			DESCRIPTION
				"Selection of output audio for pair 2"
		::= { hxc3000c01v1Entry 51 }

		-- 1.3.6.1.4.1.10106.3.101291.1.1.53
		hxc3000c01v1SelAudPair3 OBJECT-TYPE
			SYNTAX AudioMxInput5
			MAX-ACCESS read-write
			STATUS current
			DESCRIPTION
				"Selection of output audio for pair 3"
		::= { hxc3000c01v1Entry 53 }

		-- 1.3.6.1.4.1.10106.3.101291.1.1.55
		hxc3000c01v1SelAudPair4 OBJECT-TYPE
			SYNTAX AudioMxInput5
			MAX-ACCESS read-write
			STATUS current
			DESCRIPTION
				"Selection of output audio for pair 4"
		::= { hxc3000c01v1Entry 55 }

		-- 1.3.6.1.4.1.10106.3.101291.1.1.57
		hxc3000c01v1SelAudPair5 OBJECT-TYPE
			SYNTAX AudioMxInput5
			MAX-ACCESS read-write
			STATUS current
			DESCRIPTION
				"Selection of output audio for pair 5"
		::= { hxc3000c01v1Entry 57 }

		-- 1.3.6.1.4.1.10106.3.101291.1.1.59
		hxc3000c01v1SelAudPair6 OBJECT-TYPE
			SYNTAX AudioMxInput5
			MAX-ACCESS read-write
			STATUS current
			DESCRIPTION
				"Selection of output audio for pair 6"
		::= { hxc3000c01v1Entry 59 }

		-- 1.3.6.1.4.1.10106.3.101291.1.1.61
		hxc3000c01v1SelAudPair7 OBJECT-TYPE
			SYNTAX AudioMxInput5
			MAX-ACCESS read-write
			STATUS current
			DESCRIPTION
				"Selection of output audio for pair 7"
		::= { hxc3000c01v1Entry 61 }

		-- 1.3.6.1.4.1.10106.3.101291.1.1.63
		hxc3000c01v1VDelay OBJECT-TYPE
			SYNTAX DelayLines2
			MAX-ACCESS read-write
			STATUS current
			DESCRIPTION
				"Allows adjusting the video vertical delay"
		::= { hxc3000c01v1Entry 63 }

		-- 1.3.6.1.4.1.10106.3.101291.1.1.65
		hxc3000c01v1HDelay OBJECT-TYPE
			SYNTAX DelayPixel5
			MAX-ACCESS read-write
			STATUS current
			DESCRIPTION
				"Allows adjusting the video horizontal delay"
		::= { hxc3000c01v1Entry 65 }

		-- 1.3.6.1.4.1.10106.3.101291.1.1.67
		hxc3000c01v1Grp1P0Gain OBJECT-TYPE
			SYNTAX Gain24dbMute
			MAX-ACCESS read-write
			STATUS current
			DESCRIPTION
				"Group 1 pair 0 gain"
		::= { hxc3000c01v1Entry 67 }

		-- 1.3.6.1.4.1.10106.3.101291.1.1.69
		hxc3000c01v1Grp1P0Phase OBJECT-TYPE
			SYNTAX Bit0Nor1Inv
			MAX-ACCESS read-write
			STATUS current
			DESCRIPTION
				"Group 1 pair 0 phase"
		::= { hxc3000c01v1Entry 69 }

		-- 1.3.6.1.4.1.10106.3.101291.1.1.71
		hxc3000c01v1Grp1P1Gain OBJECT-TYPE
			SYNTAX Gain24dbMute
			MAX-ACCESS read-write
			STATUS current
			DESCRIPTION
				"Group 1 pair 1 gain"
		::= { hxc3000c01v1Entry 71 }

		-- 1.3.6.1.4.1.10106.3.101291.1.1.73
		hxc3000c01v1Grp1P1Phase OBJECT-TYPE
			SYNTAX Bit0Nor1Inv
			MAX-ACCESS read-write
			STATUS current
			DESCRIPTION
				"Group 1 pair 1 phase"
		::= { hxc3000c01v1Entry 73 }

		-- 1.3.6.1.4.1.10106.3.101291.1.1.75
		hxc3000c01v1Grp2P0Gain OBJECT-TYPE
			SYNTAX Gain24dbMute
			MAX-ACCESS read-write
			STATUS current
			DESCRIPTION
				"Group 2 pair 0 gain"
		::= { hxc3000c01v1Entry 75 }

		-- 1.3.6.1.4.1.10106.3.101291.1.1.77
		hxc3000c01v1Grp2P0Phase OBJECT-TYPE
			SYNTAX Bit0Nor1Inv
			MAX-ACCESS read-write
			STATUS current
			DESCRIPTION
				"Group 2 pair 0 phase"
		::= { hxc3000c01v1Entry 77 }

		-- 1.3.6.1.4.1.10106.3.101291.1.1.79
		hxc3000c01v1Grp2P1Gain OBJECT-TYPE
			SYNTAX Gain24dbMute
			MAX-ACCESS read-write
			STATUS current
			DESCRIPTION
				"Group 2 pair 1 gain"
		::= { hxc3000c01v1Entry 79 }

		-- 1.3.6.1.4.1.10106.3.101291.1.1.81
		hxc3000c01v1Grp2P1Phase OBJECT-TYPE
			SYNTAX Bit0Nor1Inv
			MAX-ACCESS read-write
			STATUS current
			DESCRIPTION
				"Group 2 pair 1 phase"
		::= { hxc3000c01v1Entry 81 }

		-- 1.3.6.1.4.1.10106.3.101291.1.1.83
		hxc3000c01v1Grp3P0Gain OBJECT-TYPE
			SYNTAX Gain24dbMute
			MAX-ACCESS read-write
			STATUS current
			DESCRIPTION
				"Group 3 pair 0 gain"
		::= { hxc3000c01v1Entry 83 }

		-- 1.3.6.1.4.1.10106.3.101291.1.1.85
		hxc3000c01v1Grp3P0Phase OBJECT-TYPE
			SYNTAX Bit0Nor1Inv
			MAX-ACCESS read-write
			STATUS current
			DESCRIPTION
				"Group 3 pair 0 phase"
		::= { hxc3000c01v1Entry 85 }

		-- 1.3.6.1.4.1.10106.3.101291.1.1.87
		hxc3000c01v1Grp3P1Gain OBJECT-TYPE
			SYNTAX Gain24dbMute
			MAX-ACCESS read-write
			STATUS current
			DESCRIPTION
				"Group 3 pair 1 gain"
		::= { hxc3000c01v1Entry 87 }

		-- 1.3.6.1.4.1.10106.3.101291.1.1.89
		hxc3000c01v1Grp3P1Phase OBJECT-TYPE
			SYNTAX Bit0Nor1Inv
			MAX-ACCESS read-write
			STATUS current
			DESCRIPTION
				"Group 3 pair 1 phase"
		::= { hxc3000c01v1Entry 89 }

		-- 1.3.6.1.4.1.10106.3.101291.1.1.91
		hxc3000c01v1Grp4P0Gain OBJECT-TYPE
			SYNTAX Gain24dbMute
			MAX-ACCESS read-write
			STATUS current
			DESCRIPTION
				"Group 4 pair 0 gain"
		::= { hxc3000c01v1Entry 91 }

		-- 1.3.6.1.4.1.10106.3.101291.1.1.93
		hxc3000c01v1Grp4P0Phase OBJECT-TYPE
			SYNTAX Bit0Nor1Inv
			MAX-ACCESS read-write
			STATUS current
			DESCRIPTION
				"Group 4 pair 0 phase"
		::= { hxc3000c01v1Entry 93 }

		-- 1.3.6.1.4.1.10106.3.101291.1.1.95
		hxc3000c01v1Grp4P1Gain OBJECT-TYPE
			SYNTAX Gain24dbMute
			MAX-ACCESS read-write
			STATUS current
			DESCRIPTION
				"Group 4 pair 1 gain"
		::= { hxc3000c01v1Entry 95 }

		-- 1.3.6.1.4.1.10106.3.101291.1.1.97
		hxc3000c01v1Grp4P1Phase OBJECT-TYPE
			SYNTAX Bit0Nor1Inv
			MAX-ACCESS read-write
			STATUS current
			DESCRIPTION
				"Group 4 pair 1 phase"
		::= { hxc3000c01v1Entry 97 }

		-- 1.3.6.1.4.1.10106.3.101291.1.1.99
		hxc3000c01v1StatFlash OBJECT-TYPE
			SYNTAX BitFailN
			MAX-ACCESS read-only
			STATUS current
			DESCRIPTION
				"Displays the Flash state"
		::= { hxc3000c01v1Entry 99 }

		-- 1.3.6.1.4.1.10106.3.101291.1.1.101
		hxc3000c01v1InPhyFail OBJECT-TYPE
			SYNTAX BitFail
			MAX-ACCESS read-only
			STATUS current
			DESCRIPTION
				"Absence fail"
		::= { hxc3000c01v1Entry 101 }

		-- 1.3.6.1.4.1.10106.3.101291.1.1.102
		hxc3000c01v1InPhyFailTrapEnable OBJECT-TYPE
			SYNTAX AlarmEnable
			MAX-ACCESS read-write
			STATUS current
			DESCRIPTION
				"Absence fail Trap Enable"
		::= { hxc3000c01v1Entry 102 }

		-- 1.3.6.1.4.1.10106.3.101291.1.1.103
		hxc3000c01v1InFmtFail OBJECT-TYPE
			SYNTAX BitFail
			MAX-ACCESS read-only
			STATUS current
			DESCRIPTION
				"Format fail"
		::= { hxc3000c01v1Entry 103 }

		-- 1.3.6.1.4.1.10106.3.101291.1.1.104
		hxc3000c01v1InFmtFailTrapEnable OBJECT-TYPE
			SYNTAX AlarmEnable
			MAX-ACCESS read-write
			STATUS current
			DESCRIPTION
				"Format fail Trap Enable"
		::= { hxc3000c01v1Entry 104 }

		-- 1.3.6.1.4.1.10106.3.101291.1.1.105
		hxc3000c01v1InIncFail OBJECT-TYPE
			SYNTAX BitFail
			MAX-ACCESS read-only
			STATUS current
			DESCRIPTION
				"Incompatible format fail"
		::= { hxc3000c01v1Entry 105 }

		-- 1.3.6.1.4.1.10106.3.101291.1.1.106
		hxc3000c01v1InIncFailTrapEnable OBJECT-TYPE
			SYNTAX AlarmEnable
			MAX-ACCESS read-write
			STATUS current
			DESCRIPTION
				"Incompatible format fail Trap Enable"
		::= { hxc3000c01v1Entry 106 }

		-- 1.3.6.1.4.1.10106.3.101291.1.1.107
		hxc3000c01v1InPresCrcFail OBJECT-TYPE
			SYNTAX BitFail
			MAX-ACCESS read-only
			STATUS current
			DESCRIPTION
				"EDH/CRC presence fail"
		::= { hxc3000c01v1Entry 107 }

		-- 1.3.6.1.4.1.10106.3.101291.1.1.109
		hxc3000c01v1InCrcFail OBJECT-TYPE
			SYNTAX BitFail
			MAX-ACCESS read-only
			STATUS current
			DESCRIPTION
				"EDH/CRC fail"
		::= { hxc3000c01v1Entry 109 }

		-- 1.3.6.1.4.1.10106.3.101291.1.1.110
		hxc3000c01v1InCrcFailTrapEnable OBJECT-TYPE
			SYNTAX AlarmEnable
			MAX-ACCESS read-write
			STATUS current
			DESCRIPTION
				"EDH/CRC fail Trap Enable"
		::= { hxc3000c01v1Entry 110 }

		-- 1.3.6.1.4.1.10106.3.101291.1.1.111
		hxc3000c01v1InPrsS352Fail OBJECT-TYPE
			SYNTAX BitFail
			MAX-ACCESS read-only
			STATUS current
			DESCRIPTION
				"SMPTE 352 presence fail"
		::= { hxc3000c01v1Entry 111 }

		-- 1.3.6.1.4.1.10106.3.101291.1.1.113
		hxc3000c01v1InS352Fail OBJECT-TYPE
			SYNTAX BitFail
			MAX-ACCESS read-only
			STATUS current
			DESCRIPTION
				"SMPTE 352 fail"
		::= { hxc3000c01v1Entry 113 }

		-- 1.3.6.1.4.1.10106.3.101291.1.1.115
		hxc3000c01v1PresS2016Fail OBJECT-TYPE
			SYNTAX BitFail
			MAX-ACCESS read-only
			STATUS current
			DESCRIPTION
				"SMPTE 2016 presence fail"
		::= { hxc3000c01v1Entry 115 }

		-- 1.3.6.1.4.1.10106.3.101291.1.1.117
		hxc3000c01v1ErrS2016Fail OBJECT-TYPE
			SYNTAX BitFail
			MAX-ACCESS read-only
			STATUS current
			DESCRIPTION
				"SMPTE 2016 error fail"
		::= { hxc3000c01v1Entry 117 }

		-- 1.3.6.1.4.1.10106.3.101291.1.1.119
		hxc3000c01v1PresAudG1Fail OBJECT-TYPE
			SYNTAX BitFail
			MAX-ACCESS read-only
			STATUS current
			DESCRIPTION
				"Audio group 1 presence fail"
		::= { hxc3000c01v1Entry 119 }

		-- 1.3.6.1.4.1.10106.3.101291.1.1.120
		hxc3000c01v1PresAudG1FailTrapEnable OBJECT-TYPE
			SYNTAX AlarmEnable
			MAX-ACCESS read-write
			STATUS current
			DESCRIPTION
				"Audio group 1 presence fail Trap Enable"
		::= { hxc3000c01v1Entry 120 }

		-- 1.3.6.1.4.1.10106.3.101291.1.1.121
		hxc3000c01v1PresAudG2Fail OBJECT-TYPE
			SYNTAX BitFail
			MAX-ACCESS read-only
			STATUS current
			DESCRIPTION
				"Audio group 2 presence fail"
		::= { hxc3000c01v1Entry 121 }

		-- 1.3.6.1.4.1.10106.3.101291.1.1.122
		hxc3000c01v1PresAudG2FailTrapEnable OBJECT-TYPE
			SYNTAX AlarmEnable
			MAX-ACCESS read-write
			STATUS current
			DESCRIPTION
				"Audio group 2 presence fail Trap Enable"
		::= { hxc3000c01v1Entry 122 }

		-- 1.3.6.1.4.1.10106.3.101291.1.1.123
		hxc3000c01v1PresAudG3Fail OBJECT-TYPE
			SYNTAX BitFail
			MAX-ACCESS read-only
			STATUS current
			DESCRIPTION
				"Audio group 3 presence fail"
		::= { hxc3000c01v1Entry 123 }

		-- 1.3.6.1.4.1.10106.3.101291.1.1.124
		hxc3000c01v1PresAudG3FailTrapEnable OBJECT-TYPE
			SYNTAX AlarmEnable
			MAX-ACCESS read-write
			STATUS current
			DESCRIPTION
				"Audio group 3 presence fail Trap Enable"
		::= { hxc3000c01v1Entry 124 }

		-- 1.3.6.1.4.1.10106.3.101291.1.1.125
		hxc3000c01v1PresAudG4Fail OBJECT-TYPE
			SYNTAX BitFail
			MAX-ACCESS read-only
			STATUS current
			DESCRIPTION
				"Audio group 4 presence fail"
		::= { hxc3000c01v1Entry 125 }

		-- 1.3.6.1.4.1.10106.3.101291.1.1.126
		hxc3000c01v1PresAudG4FailTrapEnable OBJECT-TYPE
			SYNTAX AlarmEnable
			MAX-ACCESS read-write
			STATUS current
			DESCRIPTION
				"Audio group 4 presence fail Trap Enable"
		::= { hxc3000c01v1Entry 126 }

		-- 1.3.6.1.4.1.10106.3.101291.1.1.127
		hxc3000c01v1RefFail OBJECT-TYPE
			SYNTAX BitFail
			MAX-ACCESS read-only
			STATUS current
			DESCRIPTION
				"Analog reference absence fail"
		::= { hxc3000c01v1Entry 127 }

		-- 1.3.6.1.4.1.10106.3.101291.1.1.128
		hxc3000c01v1RefFailTrapEnable OBJECT-TYPE
			SYNTAX AlarmEnable
			MAX-ACCESS read-write
			STATUS current
			DESCRIPTION
				"Analog reference absence fail Trap Enable"
		::= { hxc3000c01v1Entry 128 }

		-- 1.3.6.1.4.1.10106.3.101291.1.1.129
		hxc3000c01v1RefFmtFail OBJECT-TYPE
			SYNTAX BitFail
			MAX-ACCESS read-only
			STATUS current
			DESCRIPTION
				"Analog reference format fail"
		::= { hxc3000c01v1Entry 129 }

		-- 1.3.6.1.4.1.10106.3.101291.1.1.130
		hxc3000c01v1RefFmtFailTrapEnable OBJECT-TYPE
			SYNTAX AlarmEnable
			MAX-ACCESS read-write
			STATUS current
			DESCRIPTION
				"Analog reference format fail Trap Enable"
		::= { hxc3000c01v1Entry 130 }

		-- 1.3.6.1.4.1.10106.3.101291.1.1.131
		hxc3000c01v1LockFail OBJECT-TYPE
			SYNTAX BitFail
			MAX-ACCESS read-only
			STATUS current
			DESCRIPTION
				"Reference unlock fail"
		::= { hxc3000c01v1Entry 131 }

		-- 1.3.6.1.4.1.10106.3.101291.1.1.132
		hxc3000c01v1LockFailTrapEnable OBJECT-TYPE
			SYNTAX AlarmEnable
			MAX-ACCESS read-write
			STATUS current
			DESCRIPTION
				"Reference unlock fail Trap Enable"
		::= { hxc3000c01v1Entry 132 }

		-- 1.3.6.1.4.1.10106.3.101291.1.1.133
		hxc3000c01v1AudPair0Fail OBJECT-TYPE
			SYNTAX BitFail
			MAX-ACCESS read-only
			STATUS current
			DESCRIPTION
				"Audio pair 0 fail"
		::= { hxc3000c01v1Entry 133 }

		-- 1.3.6.1.4.1.10106.3.101291.1.1.134
		hxc3000c01v1AudPair0FailTrapEnable OBJECT-TYPE
			SYNTAX AlarmEnable
			MAX-ACCESS read-write
			STATUS current
			DESCRIPTION
				"Audio pair 0 fail Trap Enable"
		::= { hxc3000c01v1Entry 134 }

		-- 1.3.6.1.4.1.10106.3.101291.1.1.135
		hxc3000c01v1AudPair1Fail OBJECT-TYPE
			SYNTAX BitFail
			MAX-ACCESS read-only
			STATUS current
			DESCRIPTION
				"Audio pair 1 fail"
		::= { hxc3000c01v1Entry 135 }

		-- 1.3.6.1.4.1.10106.3.101291.1.1.136
		hxc3000c01v1AudPair1FailTrapEnable OBJECT-TYPE
			SYNTAX AlarmEnable
			MAX-ACCESS read-write
			STATUS current
			DESCRIPTION
				"Audio pair 1 fail Trap Enable"
		::= { hxc3000c01v1Entry 136 }

		-- 1.3.6.1.4.1.10106.3.101291.1.1.137
		hxc3000c01v1AudPair2Fail OBJECT-TYPE
			SYNTAX BitFail
			MAX-ACCESS read-only
			STATUS current
			DESCRIPTION
				"Audio pair 2 fail"
		::= { hxc3000c01v1Entry 137 }

		-- 1.3.6.1.4.1.10106.3.101291.1.1.138
		hxc3000c01v1AudPair2FailTrapEnable OBJECT-TYPE
			SYNTAX AlarmEnable
			MAX-ACCESS read-write
			STATUS current
			DESCRIPTION
				"Audio pair 2 fail Trap Enable"
		::= { hxc3000c01v1Entry 138 }

		-- 1.3.6.1.4.1.10106.3.101291.1.1.139
		hxc3000c01v1AudPair3Fail OBJECT-TYPE
			SYNTAX BitFail
			MAX-ACCESS read-only
			STATUS current
			DESCRIPTION
				"Audio pair 3 fail"
		::= { hxc3000c01v1Entry 139 }

		-- 1.3.6.1.4.1.10106.3.101291.1.1.140
		hxc3000c01v1AudPair3FailTrapEnable OBJECT-TYPE
			SYNTAX AlarmEnable
			MAX-ACCESS read-write
			STATUS current
			DESCRIPTION
				"Audio pair 3 fail Trap Enable"
		::= { hxc3000c01v1Entry 140 }

		-- 1.3.6.1.4.1.10106.3.101291.1.1.141
		hxc3000c01v1AudPair4Fail OBJECT-TYPE
			SYNTAX BitFail
			MAX-ACCESS read-only
			STATUS current
			DESCRIPTION
				"Audio pair 4 fail"
		::= { hxc3000c01v1Entry 141 }

		-- 1.3.6.1.4.1.10106.3.101291.1.1.142
		hxc3000c01v1AudPair4FailTrapEnable OBJECT-TYPE
			SYNTAX AlarmEnable
			MAX-ACCESS read-write
			STATUS current
			DESCRIPTION
				"Audio pair 4 fail Trap Enable"
		::= { hxc3000c01v1Entry 142 }

		-- 1.3.6.1.4.1.10106.3.101291.1.1.143
		hxc3000c01v1AudPair5Fail OBJECT-TYPE
			SYNTAX BitFail
			MAX-ACCESS read-only
			STATUS current
			DESCRIPTION
				"Audio pair 5 fail"
		::= { hxc3000c01v1Entry 143 }

		-- 1.3.6.1.4.1.10106.3.101291.1.1.144
		hxc3000c01v1AudPair5FailTrapEnable OBJECT-TYPE
			SYNTAX AlarmEnable
			MAX-ACCESS read-write
			STATUS current
			DESCRIPTION
				"Audio pair 5 fail Trap Enable"
		::= { hxc3000c01v1Entry 144 }

		-- 1.3.6.1.4.1.10106.3.101291.1.1.145
		hxc3000c01v1AudPair6Fail OBJECT-TYPE
			SYNTAX BitFail
			MAX-ACCESS read-only
			STATUS current
			DESCRIPTION
				"Audio pair 6 fail"
		::= { hxc3000c01v1Entry 145 }

		-- 1.3.6.1.4.1.10106.3.101291.1.1.146
		hxc3000c01v1AudPair6FailTrapEnable OBJECT-TYPE
			SYNTAX AlarmEnable
			MAX-ACCESS read-write
			STATUS current
			DESCRIPTION
				"Audio pair 6 fail Trap Enable"
		::= { hxc3000c01v1Entry 146 }

		-- 1.3.6.1.4.1.10106.3.101291.1.1.147
		hxc3000c01v1AudPair7Fail OBJECT-TYPE
			SYNTAX BitFail
			MAX-ACCESS read-only
			STATUS current
			DESCRIPTION
				"Audio pair 7 fail"
		::= { hxc3000c01v1Entry 147 }

		-- 1.3.6.1.4.1.10106.3.101291.1.1.148
		hxc3000c01v1AudPair7FailTrapEnable OBJECT-TYPE
			SYNTAX AlarmEnable
			MAX-ACCESS read-write
			STATUS current
			DESCRIPTION
				"Audio pair 7 fail Trap Enable"
		::= { hxc3000c01v1Entry 148 }

		-- 1.3.6.1.4.1.10106.3.101291.1.1.149
		hxc3000c01v1InAfdDetct OBJECT-TYPE
			SYNTAX Afd1
			MAX-ACCESS read-only
			STATUS current
			DESCRIPTION
				"Input detected AFD"
		::= { hxc3000c01v1Entry 149 }

		-- 1.3.6.1.4.1.10106.3.101291.1.1.150
		hxc3000c01v1InAfdDetctTrapEnable OBJECT-TYPE
			SYNTAX AlarmEnable
			MAX-ACCESS read-write
			STATUS current
			DESCRIPTION
				"Input detected AFD Trap Enable"
		::= { hxc3000c01v1Entry 150 }

		-- 1.3.6.1.4.1.10106.3.101291.1.1.151
		hxc3000c01v1InCfDetct OBJECT-TYPE
			SYNTAX Cf1
			MAX-ACCESS read-only
			STATUS current
			DESCRIPTION
				"Input detected coded frame"
		::= { hxc3000c01v1Entry 151 }

		-- 1.3.6.1.4.1.10106.3.101291.1.1.152
		hxc3000c01v1InCfDetctTrapEnable OBJECT-TYPE
			SYNTAX AlarmEnable
			MAX-ACCESS read-write
			STATUS current
			DESCRIPTION
				"Input detected coded frame Trap Enable"
		::= { hxc3000c01v1Entry 152 }

		-- 1.3.6.1.4.1.10106.3.101291.1.1.153
		hxc3000c01v1InFormat OBJECT-TYPE
			SYNTAX SdiHd3gFmt3
			MAX-ACCESS read-only
			STATUS current
			DESCRIPTION
				"Input format"
		::= { hxc3000c01v1Entry 153 }

		-- 1.3.6.1.4.1.10106.3.101291.1.1.154
		hxc3000c01v1InFormatTrapEnable OBJECT-TYPE
			SYNTAX AlarmEnable
			MAX-ACCESS read-write
			STATUS current
			DESCRIPTION
				"Input format Trap Enable"
		::= { hxc3000c01v1Entry 154 }

		-- 1.3.6.1.4.1.10106.3.101291.1.1.155
		hxc3000c01v1RefFormat OBJECT-TYPE
			SYNTAX SdiHd3gFmt3
			MAX-ACCESS read-only
			STATUS current
			DESCRIPTION
				"Reference format"
		::= { hxc3000c01v1Entry 155 }

		-- 1.3.6.1.4.1.10106.3.101291.1.1.156
		hxc3000c01v1RefFormatTrapEnable OBJECT-TYPE
			SYNTAX AlarmEnable
			MAX-ACCESS read-write
			STATUS current
			DESCRIPTION
				"Reference format Trap Enable"
		::= { hxc3000c01v1Entry 156 }

		-- 1.3.6.1.4.1.10106.3.101291.1.1.157
		hxc3000c01v1TxFormat OBJECT-TYPE
			SYNTAX SdiHd3gFmt3
			MAX-ACCESS read-only
			STATUS current
			DESCRIPTION
				"Output format"
		::= { hxc3000c01v1Entry 157 }

		-- 1.3.6.1.4.1.10106.3.101291.1.1.158
		hxc3000c01v1TxFormatTrapEnable OBJECT-TYPE
			SYNTAX AlarmEnable
			MAX-ACCESS read-write
			STATUS current
			DESCRIPTION
				"Output format Trap Enable"
		::= { hxc3000c01v1Entry 158 }

		-- 1.3.6.1.4.1.10106.3.101291.1.1.159
		hxc3000c01v1TxtPres OBJECT-TYPE
			SYNTAX BitFailN
			MAX-ACCESS read-only
			STATUS current
			DESCRIPTION
				"TXT presence"
		::= { hxc3000c01v1Entry 159 }

		-- 1.3.6.1.4.1.10106.3.101291.1.1.161
		hxc3000c01v1VitcPres OBJECT-TYPE
			SYNTAX BitFailN
			MAX-ACCESS read-only
			STATUS current
			DESCRIPTION
				"VITC presence"
		::= { hxc3000c01v1Entry 161 }

		-- 1.3.6.1.4.1.10106.3.101291.1.1.163
		hxc3000c01v1Mute OBJECT-TYPE
			SYNTAX Bit0No1Yes
			MAX-ACCESS read-only
			STATUS current
			DESCRIPTION
				"Muted output"
		::= { hxc3000c01v1Entry 163 }

		-- 1.3.6.1.4.1.10106.3.101291.1.1.165
		hxc3000c01v1Black OBJECT-TYPE
			SYNTAX Bit0No1Yes
			MAX-ACCESS read-only
			STATUS current
			DESCRIPTION
				"Black output"
		::= { hxc3000c01v1Entry 165 }

		-- 1.3.6.1.4.1.10106.3.101291.1.1.167
		hxc3000c01v1Gpi1 OBJECT-TYPE
			SYNTAX Bit0Off1On
			MAX-ACCESS read-only
			STATUS current
			DESCRIPTION
				"Transmitted GPI1"
		::= { hxc3000c01v1Entry 167 }

		-- 1.3.6.1.4.1.10106.3.101291.1.1.169
		hxc3000c01v1Gpi2 OBJECT-TYPE
			SYNTAX Bit0Off1On
			MAX-ACCESS read-only
			STATUS current
			DESCRIPTION
				"Transmitted GPI2"
		::= { hxc3000c01v1Entry 169 }

		-- 1.3.6.1.4.1.10106.3.101291.1.1.171
		hxc3000c01v1Gpi3 OBJECT-TYPE
			SYNTAX Bit0Off1On
			MAX-ACCESS read-only
			STATUS current
			DESCRIPTION
				"Transmitted GPI3"
		::= { hxc3000c01v1Entry 171 }

		-- 1.3.6.1.4.1.10106.3.101291.1.1.173
		hxc3000c01v1Gpi4 OBJECT-TYPE
			SYNTAX Bit0Off1On
			MAX-ACCESS read-only
			STATUS current
			DESCRIPTION
				"Transmitted GPI4"
		::= { hxc3000c01v1Entry 173 }

		-- 1.3.6.1.4.1.10106.3.101291.1.1.175
		hxc3000c01v1SerialNo OBJECT-TYPE
			SYNTAX SerialNo
			MAX-ACCESS read-only
			STATUS current
			DESCRIPTION
				"Serial number"
		::= { hxc3000c01v1Entry 175 }

		-- 1.3.6.1.4.1.10106.3.101291.1.1.177
		hxc3000c01v1MuteEna OBJECT-TYPE
			SYNTAX Bit0No1Yes
			MAX-ACCESS read-write
			STATUS current
			DESCRIPTION
				"Enables outputs mute"
		::= { hxc3000c01v1Entry 177 }

		-- 1.3.6.1.4.1.10106.3.454401
		hsw2000c01v1 OBJECT IDENTIFIER ::= { albalaProducts 454401 }

		-- 1.3.6.1.4.1.10106.3.454401.1
		hsw2000c01v1Table  OBJECT-TYPE
			SYNTAX SEQUENCE OF Hsw2000c01v1Entry
			MAX-ACCESS not-accessible
			STATUS current
			DESCRIPTION
				"Module  HSW2000C01V1 Table"
			::= { hsw2000c01v1 1 }

		-- 1.3.6.1.4.1.10106.3.454401.1.1
		hsw2000c01v1Entry  OBJECT-TYPE
			SYNTAX Hsw2000c01v1Entry
			MAX-ACCESS not-accessible
			STATUS current
			DESCRIPTION
				"Module HSW2000C01V1 Entry"
			INDEX { hsw2000c01v1Index }
			::= { hsw2000c01v1Table 1 }

			Hsw2000c01v1Entry ::=
			SEQUENCE {
				hsw2000c01v1Index
				ModuleIndex,
				hsw2000c01v1ActivePreset
				PresetActive,
				hsw2000c01v1LoadPreset
				PresetLoad,
				hsw2000c01v1SavePreset
				PresetSave,
				hsw2000c01v1StateSel
				HswState,
				hsw2000c01v1StateSelTrapEnable
				AlarmEnable,
				hsw2000c01v1SwitchMode
				Hsw2SwMode,
				hsw2000c01v1SwitchModeTrapEnable
				AlarmEnable,
				hsw2000c01v1FreezeMode
				HswFreezeMode,
				hsw2000c01v1BypassEnable
				Bit0Dis1Ena,
				hsw2000c01v1BypassEnableTrapEnable
				AlarmEnable,
				hsw2000c01v1InpFailMode
				Bit0No1Yes,
				hsw2000c01v1StateAMap
				HswMapState,
				hsw2000c01v1StateBMap
				HswMapState,
				hsw2000c01v1AnaRefFmt
				SdiHd3gFmt5,
				hsw2000c01v1In1StChange
				Bit0No1Yes,
				hsw2000c01v1In2StChange
				Bit0No1Yes,
				hsw2000c01v1InputChange
				Bit0No1Yes,
				hsw2000c01v1DePer2IncIn1
				Bit0Dis1Ena,
				hsw2000c01v1DePer2IncIn2
				Bit0Dis1Ena,
				hsw2000c01v1VDelay
				DelayLines2,
				hsw2000c01v1HDelay
				DelayPixel5,
				hsw2000c01v1Holdoff
				TimeS2,
				hsw2000c01v1PhyFailTim
				HswTiming,
				hsw2000c01v1FmtFailTim
				HswTiming,
				hsw2000c01v1IncFailTim
				HswTiming,
				hsw2000c01v1StatusMode
				StatusMode,
				hsw2000c01v1SynchroModeIn1
				Bit0Fra1Lin,
				hsw2000c01v1SynchroModeIn2
				Bit0Fra1Lin,
				hsw2000c01v1BlkFailTim
				HswTiming,
				hsw2000c01v1FrzFailTim
				HswTiming,
				hsw2000c01v1PatFailTim
				HswTiming,
				hsw2000c01v1CrcFailTim
				HswTiming,
				hsw2000c01v1SilFailTim
				HswTiming,
				hsw2000c01v1OvrFailTim
				HswTiming,
				hsw2000c01v1PhFailTim
				HswTiming,
				hsw2000c01v1PresFailTim
				HswTiming,
				hsw2000c01v1ActPer1
				TimeS2,
				hsw2000c01v1DeactPer1
				TimeS2,
				hsw2000c01v1ActPer2
				TimeS2,
				hsw2000c01v1DeactPer2
				TimeS2,
				hsw2000c01v1CrcThreshold
				Rate2,
				hsw2000c01v1BlackThreshold
				BlackThreshold,
				hsw2000c01v1VertFrozenWin
				Rate1,
				hsw2000c01v1HtalFrozenWin
				Rate1,
				hsw2000c01v1In1PhyFailMsk
				BitMask,
				hsw2000c01v1In1FmtFailMsk
				BitMask,
				hsw2000c01v1In1IncFailMsk
				BitMask,
				hsw2000c01v1In1BlkFailMsk
				BitMask,
				hsw2000c01v1In1FrzFailMsk
				BitMask,
				hsw2000c01v1In1PatFailMsk
				BitMask,
				hsw2000c01v1In1CrcFailMsk
				BitMask,
				hsw2000c01v1In1SilFailMsk
				BitMask,
				hsw2000c01v1In1OvrFailMsk
				BitMask,
				hsw2000c01v1In1PhFailMsk
				BitMask,
				hsw2000c01v1In1PreFailMsk
				BitMask,
				hsw2000c01v1In2PhyFailMsk
				BitMask,
				hsw2000c01v1In2FmtFailMsk
				BitMask,
				hsw2000c01v1In2IncFailMsk
				BitMask,
				hsw2000c01v1In2BlkFailMsk
				BitMask,
				hsw2000c01v1In2FrzFailMsk
				BitMask,
				hsw2000c01v1In2PatFailMsk
				BitMask,
				hsw2000c01v1In2CrcFailMsk
				BitMask,
				hsw2000c01v1In2SilFailMsk
				BitMask,
				hsw2000c01v1In2OvrFailMsk
				BitMask,
				hsw2000c01v1In2PhFailMsk
				BitMask,
				hsw2000c01v1In2PreFailMsk
				BitMask,
				hsw2000c01v1RefFailMsk
				BitMask,
				hsw2000c01v1LockFailMsk
				BitMask,
				hsw2000c01v1In1AudG1p0Msk
				AudioMask,
				hsw2000c01v1In1AudG1p1Msk
				AudioMask,
				hsw2000c01v1In1AudG2p0Msk
				AudioMask,
				hsw2000c01v1In1AudG2p1Msk
				AudioMask,
				hsw2000c01v1In1AudG3p0Msk
				AudioMask,
				hsw2000c01v1In1AudG3p1Msk
				AudioMask,
				hsw2000c01v1In1AudG4p0Msk
				AudioMask,
				hsw2000c01v1In1AudG4p1Msk
				AudioMask,
				hsw2000c01v1In2AudG1p0Msk
				AudioMask,
				hsw2000c01v1In2AudG1p1Msk
				AudioMask,
				hsw2000c01v1In2AudG2p0Msk
				AudioMask,
				hsw2000c01v1In2AudG2p1Msk
				AudioMask,
				hsw2000c01v1In2AudG3p0Msk
				AudioMask,
				hsw2000c01v1In2AudG3p1Msk
				AudioMask,
				hsw2000c01v1In2AudG4p0Msk
				AudioMask,
				hsw2000c01v1In2AudG4p1Msk
				AudioMask,
				hsw2000c01v1FrzToBckTime
				TimeS2,
				hsw2000c01v1SilenceLevel
				LevelDbfs3,
				hsw2000c01v1SilenceTime
				TimeS2,
				hsw2000c01v1OverloadLevel
				LevelDbfs4,
				hsw2000c01v1TxtLinesThrs
				TxtThreshold,
				hsw2000c01v1In1Fail
				BitFail,
				hsw2000c01v1In1FailTrapEnable
				AlarmEnable,
				hsw2000c01v1In2Fail
				BitFail,
				hsw2000c01v1In2FailTrapEnable
				AlarmEnable,
				hsw2000c01v1EqualPid
				UmidStatus,
				hsw2000c01v1EqualPidTrapEnable
				AlarmEnable,
				hsw2000c01v1SelOut1
				HswOutput,
				hsw2000c01v1SelOut1TrapEnable
				AlarmEnable,
				hsw2000c01v1SelOut2
				HswOutput,
				hsw2000c01v1SelOut2TrapEnable
				AlarmEnable,
				hsw2000c01v1EqualUmid
				UmidStatus,
				hsw2000c01v1EqualUmidTrapEnable
				AlarmEnable,
				hsw2000c01v1In1PhyFail
				BitFail,
				hsw2000c01v1In1PhyFailTrapEnable
				AlarmEnable,
				hsw2000c01v1In1FmtFail
				BitFail,
				hsw2000c01v1In1FmtFailTrapEnable
				AlarmEnable,
				hsw2000c01v1In1IncFail
				BitFail,
				hsw2000c01v1In1IncFailTrapEnable
				AlarmEnable,
				hsw2000c01v1In1BlkFail
				BitFail,
				hsw2000c01v1In1BlkFailTrapEnable
				AlarmEnable,
				hsw2000c01v1In1FrzFail
				BitFail,
				hsw2000c01v1In1FrzFailTrapEnable
				AlarmEnable,
				hsw2000c01v1In1PatFail
				BitFail,
				hsw2000c01v1In1PatFailTrapEnable
				AlarmEnable,
				hsw2000c01v1In1CrcFail
				BitFail,
				hsw2000c01v1In1CrcFailTrapEnable
				AlarmEnable,
				hsw2000c01v1In1SilFail
				BitFail,
				hsw2000c01v1In1SilFailTrapEnable
				AlarmEnable,
				hsw2000c01v1In1OvrFail
				BitFail,
				hsw2000c01v1In1OvrFailTrapEnable
				AlarmEnable,
				hsw2000c01v1In1PhFail
				BitFail,
				hsw2000c01v1In1PhFailTrapEnable
				AlarmEnable,
				hsw2000c01v1In1PreFail
				BitFail,
				hsw2000c01v1In1PreFailTrapEnable
				AlarmEnable,
				hsw2000c01v1In2PhyFail
				BitFail,
				hsw2000c01v1In2PhyFailTrapEnable
				AlarmEnable,
				hsw2000c01v1In2FmtFail
				BitFail,
				hsw2000c01v1In2FmtFailTrapEnable
				AlarmEnable,
				hsw2000c01v1In2IncFail
				BitFail,
				hsw2000c01v1In2IncFailTrapEnable
				AlarmEnable,
				hsw2000c01v1In2BlkFail
				BitFail,
				hsw2000c01v1In2BlkFailTrapEnable
				AlarmEnable,
				hsw2000c01v1In2FrzFail
				BitFail,
				hsw2000c01v1In2FrzFailTrapEnable
				AlarmEnable,
				hsw2000c01v1In2PatFail
				BitFail,
				hsw2000c01v1In2PatFailTrapEnable
				AlarmEnable,
				hsw2000c01v1In2CrcFail
				BitFail,
				hsw2000c01v1In2CrcFailTrapEnable
				AlarmEnable,
				hsw2000c01v1In2SilFail
				BitFail,
				hsw2000c01v1In2SilFailTrapEnable
				AlarmEnable,
				hsw2000c01v1In2OvrFail
				BitFail,
				hsw2000c01v1In2OvrFailTrapEnable
				AlarmEnable,
				hsw2000c01v1In2PhFail
				BitFail,
				hsw2000c01v1In2PhFailTrapEnable
				AlarmEnable,
				hsw2000c01v1In2PreFail
				BitFail,
				hsw2000c01v1In2PreFailTrapEnable
				AlarmEnable,
				hsw2000c01v1RefFail
				BitFail,
				hsw2000c01v1RefFailTrapEnable
				AlarmEnable,
				hsw2000c01v1LockFail
				BitFail,
				hsw2000c01v1LockFailTrapEnable
				AlarmEnable,
				hsw2000c01v1In1Format
				SdiHd3gFmt3,
				hsw2000c01v1In1FormatTrapEnable
				AlarmEnable,
				hsw2000c01v1In2Format
				SdiHd3gFmt3,
				hsw2000c01v1In2FormatTrapEnable
				AlarmEnable,
				hsw2000c01v1RefFormat
				SdiHd3gFmt3,
				hsw2000c01v1RefFormatTrapEnable
				AlarmEnable,
				hsw2000c01v1In1PidPres
				Bit0No1Yes,
				hsw2000c01v1In2PidPres
				Bit0No1Yes,
				hsw2000c01v1In1UmidPres
				Bit0No1Yes,
				hsw2000c01v1In2UmidPres
				Bit0No1Yes,
				hsw2000c01v1In1Grp1Pres
				Bit0No1Yes,
				hsw2000c01v1In1Grp1PresTrapEnable
				AlarmEnable,
				hsw2000c01v1In1Grp2Pres
				Bit0No1Yes,
				hsw2000c01v1In1Grp2PresTrapEnable
				AlarmEnable,
				hsw2000c01v1In1Grp3Pres
				Bit0No1Yes,
				hsw2000c01v1In1Grp3PresTrapEnable
				AlarmEnable,
				hsw2000c01v1In1Grp4Pres
				Bit0No1Yes,
				hsw2000c01v1In1Grp4PresTrapEnable
				AlarmEnable,
				hsw2000c01v1In1Grp1P0Stat
				AudioStatus,
				hsw2000c01v1In1Grp1P0StatTrapEnable
				AlarmEnable,
				hsw2000c01v1In1Grp1P1Stat
				AudioStatus,
				hsw2000c01v1In1Grp1P1StatTrapEnable
				AlarmEnable,
				hsw2000c01v1In1Grp2P0Stat
				AudioStatus,
				hsw2000c01v1In1Grp2P0StatTrapEnable
				AlarmEnable,
				hsw2000c01v1In1Grp2P1Stat
				AudioStatus,
				hsw2000c01v1In1Grp2P1StatTrapEnable
				AlarmEnable,
				hsw2000c01v1In1Grp3P0Stat
				AudioStatus,
				hsw2000c01v1In1Grp3P0StatTrapEnable
				AlarmEnable,
				hsw2000c01v1In1Grp3P1Stat
				AudioStatus,
				hsw2000c01v1In1Grp3P1StatTrapEnable
				AlarmEnable,
				hsw2000c01v1In1Grp4P0Stat
				AudioStatus,
				hsw2000c01v1In1Grp4P0StatTrapEnable
				AlarmEnable,
				hsw2000c01v1In1Grp4P1Stat
				AudioStatus,
				hsw2000c01v1In1Grp4P1StatTrapEnable
				AlarmEnable,
				hsw2000c01v1In2Grp1Pres
				Bit0No1Yes,
				hsw2000c01v1In2Grp1PresTrapEnable
				AlarmEnable,
				hsw2000c01v1In2Grp2Pres
				Bit0No1Yes,
				hsw2000c01v1In2Grp2PresTrapEnable
				AlarmEnable,
				hsw2000c01v1In2Grp3Pres
				Bit0No1Yes,
				hsw2000c01v1In2Grp3PresTrapEnable
				AlarmEnable,
				hsw2000c01v1In2Grp4Pres
				Bit0No1Yes,
				hsw2000c01v1In2Grp4PresTrapEnable
				AlarmEnable,
				hsw2000c01v1In2Grp1P0Stat
				AudioStatus,
				hsw2000c01v1In2Grp1P0StatTrapEnable
				AlarmEnable,
				hsw2000c01v1In2Grp1P1Stat
				AudioStatus,
				hsw2000c01v1In2Grp1P1StatTrapEnable
				AlarmEnable,
				hsw2000c01v1In2Grp2P0Stat
				AudioStatus,
				hsw2000c01v1In2Grp2P0StatTrapEnable
				AlarmEnable,
				hsw2000c01v1In2Grp2P1Stat
				AudioStatus,
				hsw2000c01v1In2Grp2P1StatTrapEnable
				AlarmEnable,
				hsw2000c01v1In2Grp3P0Stat
				AudioStatus,
				hsw2000c01v1In2Grp3P0StatTrapEnable
				AlarmEnable,
				hsw2000c01v1In2Grp3P1Stat
				AudioStatus,
				hsw2000c01v1In2Grp3P1StatTrapEnable
				AlarmEnable,
				hsw2000c01v1In2Grp4P0Stat
				AudioStatus,
				hsw2000c01v1In2Grp4P0StatTrapEnable
				AlarmEnable,
				hsw2000c01v1In2Grp4P1Stat
				AudioStatus,
				hsw2000c01v1In2Grp4P1StatTrapEnable
				AlarmEnable,
				hsw2000c01v1In1WssCod
				Code4Bit,
				hsw2000c01v1In1WssCodTrapEnable
				AlarmEnable,
				hsw2000c01v1In1WssStat
				AfdInfo,
				hsw2000c01v1In1WssStatTrapEnable
				AlarmEnable,
				hsw2000c01v1In1ViiAfdCod
				Code4Bit,
				hsw2000c01v1In1ViiAfdCodTrapEnable
				AlarmEnable,
				hsw2000c01v1In1ViiStat
				AfdInfo,
				hsw2000c01v1In1ViiStatTrapEnable
				AlarmEnable,
				hsw2000c01v1In12016AfdCod
				Code4Bit,
				hsw2000c01v1In12016AfdCodTrapEnable
				AlarmEnable,
				hsw2000c01v1In12016Stat
				AfdInfo,
				hsw2000c01v1In12016StatTrapEnable
				AlarmEnable,
				hsw2000c01v1In2WssCod
				Code4Bit,
				hsw2000c01v1In2WssCodTrapEnable
				AlarmEnable,
				hsw2000c01v1In2WssStat
				AfdInfo,
				hsw2000c01v1In2WssStatTrapEnable
				AlarmEnable,
				hsw2000c01v1In2ViiAfdCod
				Code4Bit,
				hsw2000c01v1In2ViiAfdCodTrapEnable
				AlarmEnable,
				hsw2000c01v1In2ViiStat
				AfdInfo,
				hsw2000c01v1In2ViiStatTrapEnable
				AlarmEnable,
				hsw2000c01v1In22016Cod
				Code4Bit,
				hsw2000c01v1In22016CodTrapEnable
				AlarmEnable,
				hsw2000c01v1In22016Stat
				AfdInfo,
				hsw2000c01v1In22016StatTrapEnable
				AlarmEnable,
				hsw2000c01v1In1TxtLinLow
				Bit0No1Yes,
				hsw2000c01v1In1TxtLinLowTrapEnable
				AlarmEnable,
				hsw2000c01v1In1TxtLin1s
				Uint11,
				hsw2000c01v1In2TxtLinLow
				Bit0No1Yes,
				hsw2000c01v1In2TxtLinLowTrapEnable
				AlarmEnable,
				hsw2000c01v1In2TxtLin1s
				Uint11,
				hsw2000c01v1SerialNo
				SerialNo
			 }

		-- 1.3.6.1.4.1.10106.3.101291.1.1.1
		hsw2000c01v1Index OBJECT-TYPE
			SYNTAX ModuleIndex
			MAX-ACCESS read-only
			STATUS current
			DESCRIPTION
				"Index of HSW2000C01V1 Table"
		::= { hsw2000c01v1Entry 1 }

		-- 1.3.6.1.4.1.10106.3.101291.1.1.3
		hsw2000c01v1ActivePreset OBJECT-TYPE
			SYNTAX PresetActive
			MAX-ACCESS read-only
			STATUS current
			DESCRIPTION
				"Shows the active preset"
		::= { hsw2000c01v1Entry 3 }

		-- 1.3.6.1.4.1.10106.3.101291.1.1.5
		hsw2000c01v1LoadPreset OBJECT-TYPE
			SYNTAX PresetLoad
			MAX-ACCESS read-write
			STATUS current
			DESCRIPTION
				"Allows loading a preset"
		::= { hsw2000c01v1Entry 5 }

		-- 1.3.6.1.4.1.10106.3.101291.1.1.7
		hsw2000c01v1SavePreset OBJECT-TYPE
			SYNTAX PresetSave
			MAX-ACCESS read-write
			STATUS current
			DESCRIPTION
				"Allows saving a preset"
		::= { hsw2000c01v1Entry 7 }

		-- 1.3.6.1.4.1.10106.3.101291.1.1.9
		hsw2000c01v1StateSel OBJECT-TYPE
			SYNTAX HswState
			MAX-ACCESS read-write
			STATUS current
			DESCRIPTION
				"Shows the module's current state"
		::= { hsw2000c01v1Entry 9 }

		-- 1.3.6.1.4.1.10106.3.101291.1.1.10
		hsw2000c01v1StateSelTrapEnable OBJECT-TYPE
			SYNTAX AlarmEnable
			MAX-ACCESS read-write
			STATUS current
			DESCRIPTION
				"Shows the module's current state Trap Enable"
		::= { hsw2000c01v1Entry 10 }

		-- 1.3.6.1.4.1.10106.3.101291.1.1.11
		hsw2000c01v1SwitchMode OBJECT-TYPE
			SYNTAX Hsw2SwMode
			MAX-ACCESS read-write
			STATUS current
			DESCRIPTION
				"Allows selecting the switching mode"
		::= { hsw2000c01v1Entry 11 }

		-- 1.3.6.1.4.1.10106.3.101291.1.1.12
		hsw2000c01v1SwitchModeTrapEnable OBJECT-TYPE
			SYNTAX AlarmEnable
			MAX-ACCESS read-write
			STATUS current
			DESCRIPTION
				"Allows selecting the switching mode Trap Enable"
		::= { hsw2000c01v1Entry 12 }

		-- 1.3.6.1.4.1.10106.3.101291.1.1.13
		hsw2000c01v1FreezeMode OBJECT-TYPE
			SYNTAX HswFreezeMode
			MAX-ACCESS read-write
			STATUS current
			DESCRIPTION
				"Allows selecting the freeze detection mode"
		::= { hsw2000c01v1Entry 13 }

		-- 1.3.6.1.4.1.10106.3.101291.1.1.15
		hsw2000c01v1BypassEnable OBJECT-TYPE
			SYNTAX Bit0Dis1Ena
			MAX-ACCESS read-write
			STATUS current
			DESCRIPTION
				"Allows activating the rear board bypass"
		::= { hsw2000c01v1Entry 15 }

		-- 1.3.6.1.4.1.10106.3.101291.1.1.16
		hsw2000c01v1BypassEnableTrapEnable OBJECT-TYPE
			SYNTAX AlarmEnable
			MAX-ACCESS read-write
			STATUS current
			DESCRIPTION
				"Allows activating the rear board bypass Trap Enable"
		::= { hsw2000c01v1Entry 16 }

		-- 1.3.6.1.4.1.10106.3.101291.1.1.17
		hsw2000c01v1InpFailMode OBJECT-TYPE
			SYNTAX Bit0No1Yes
			MAX-ACCESS read-write
			STATUS current
			DESCRIPTION
				"Selects if the output is muted when the selected input fails"
		::= { hsw2000c01v1Entry 17 }

		-- 1.3.6.1.4.1.10106.3.101291.1.1.19
		hsw2000c01v1StateAMap OBJECT-TYPE
			SYNTAX HswMapState
			MAX-ACCESS read-write
			STATUS current
			DESCRIPTION
				"Allow selecting the input to output mapping when state A is selected"
		::= { hsw2000c01v1Entry 19 }

		-- 1.3.6.1.4.1.10106.3.101291.1.1.21
		hsw2000c01v1StateBMap OBJECT-TYPE
			SYNTAX HswMapState
			MAX-ACCESS read-write
			STATUS current
			DESCRIPTION
				"Allow selecting the input to output mapping when state B is selected"
		::= { hsw2000c01v1Entry 21 }

		-- 1.3.6.1.4.1.10106.3.101291.1.1.23
		hsw2000c01v1AnaRefFmt OBJECT-TYPE
			SYNTAX SdiHd3gFmt5
			MAX-ACCESS read-write
			STATUS current
			DESCRIPTION
				"Analog reference input format"
		::= { hsw2000c01v1Entry 23 }

		-- 1.3.6.1.4.1.10106.3.101291.1.1.25
		hsw2000c01v1In1StChange OBJECT-TYPE
			SYNTAX Bit0No1Yes
			MAX-ACCESS read-write
			STATUS current
			DESCRIPTION
				"Signals a change in fail status"
		::= { hsw2000c01v1Entry 25 }

		-- 1.3.6.1.4.1.10106.3.101291.1.1.27
		hsw2000c01v1In2StChange OBJECT-TYPE
			SYNTAX Bit0No1Yes
			MAX-ACCESS read-write
			STATUS current
			DESCRIPTION
				"Signals a change in fail status"
		::= { hsw2000c01v1Entry 27 }

		-- 1.3.6.1.4.1.10106.3.101291.1.1.29
		hsw2000c01v1InputChange OBJECT-TYPE
			SYNTAX Bit0No1Yes
			MAX-ACCESS read-write
			STATUS current
			DESCRIPTION
				"Signals a change in selected input"
		::= { hsw2000c01v1Entry 29 }

		-- 1.3.6.1.4.1.10106.3.101291.1.1.31
		hsw2000c01v1DePer2IncIn1 OBJECT-TYPE
			SYNTAX Bit0Dis1Ena
			MAX-ACCESS read-write
			STATUS current
			DESCRIPTION
				"Allows increasing deactivation time of timing 2 for inpu1 in 500ms"
		::= { hsw2000c01v1Entry 31 }

		-- 1.3.6.1.4.1.10106.3.101291.1.1.33
		hsw2000c01v1DePer2IncIn2 OBJECT-TYPE
			SYNTAX Bit0Dis1Ena
			MAX-ACCESS read-write
			STATUS current
			DESCRIPTION
				"Allows increasing deactivation time of timing 2 for inpu2 in 500ms"
		::= { hsw2000c01v1Entry 33 }

		-- 1.3.6.1.4.1.10106.3.101291.1.1.35
		hsw2000c01v1VDelay OBJECT-TYPE
			SYNTAX DelayLines2
			MAX-ACCESS read-write
			STATUS current
			DESCRIPTION
				"Allows adjusting the video vertical delay"
		::= { hsw2000c01v1Entry 35 }

		-- 1.3.6.1.4.1.10106.3.101291.1.1.37
		hsw2000c01v1HDelay OBJECT-TYPE
			SYNTAX DelayPixel5
			MAX-ACCESS read-write
			STATUS current
			DESCRIPTION
				"Allows adjusting the video horizontal delay"
		::= { hsw2000c01v1Entry 37 }

		-- 1.3.6.1.4.1.10106.3.101291.1.1.39
		hsw2000c01v1Holdoff OBJECT-TYPE
			SYNTAX TimeS2
			MAX-ACCESS read-write
			STATUS current
			DESCRIPTION
				"Elapsed time after a switch event before a new switch occurs"
		::= { hsw2000c01v1Entry 39 }

		-- 1.3.6.1.4.1.10106.3.101291.1.1.41
		hsw2000c01v1PhyFailTim OBJECT-TYPE
			SYNTAX HswTiming
			MAX-ACCESS read-write
			STATUS current
			DESCRIPTION
				"Allows selecting the desired timing for the physical fail"
		::= { hsw2000c01v1Entry 41 }

		-- 1.3.6.1.4.1.10106.3.101291.1.1.43
		hsw2000c01v1FmtFailTim OBJECT-TYPE
			SYNTAX HswTiming
			MAX-ACCESS read-write
			STATUS current
			DESCRIPTION
				"Allows selecting the desired timing for the format fail"
		::= { hsw2000c01v1Entry 43 }

		-- 1.3.6.1.4.1.10106.3.101291.1.1.45
		hsw2000c01v1IncFailTim OBJECT-TYPE
			SYNTAX HswTiming
			MAX-ACCESS read-write
			STATUS current
			DESCRIPTION
				"Allows selecting the desired timing for the incompatible format fail"
		::= { hsw2000c01v1Entry 45 }

		-- 1.3.6.1.4.1.10106.3.101291.1.1.47
		hsw2000c01v1StatusMode OBJECT-TYPE
			SYNTAX StatusMode
			MAX-ACCESS read-write
			STATUS current
			DESCRIPTION
				"Allows selecting if status informaction is afected by activation/desactivation timing"
		::= { hsw2000c01v1Entry 47 }

		-- 1.3.6.1.4.1.10106.3.101291.1.1.49
		hsw2000c01v1SynchroModeIn1 OBJECT-TYPE
			SYNTAX Bit0Fra1Lin
			MAX-ACCESS read-write
			STATUS current
			DESCRIPTION
				"Allows selecting the synchronizing mode"
		::= { hsw2000c01v1Entry 49 }

		-- 1.3.6.1.4.1.10106.3.101291.1.1.51
		hsw2000c01v1SynchroModeIn2 OBJECT-TYPE
			SYNTAX Bit0Fra1Lin
			MAX-ACCESS read-write
			STATUS current
			DESCRIPTION
				"Allows selecting the synchronizing mode"
		::= { hsw2000c01v1Entry 51 }

		-- 1.3.6.1.4.1.10106.3.101291.1.1.53
		hsw2000c01v1BlkFailTim OBJECT-TYPE
			SYNTAX HswTiming
			MAX-ACCESS read-write
			STATUS current
			DESCRIPTION
				"Allows selecting the desired timing for the black fail"
		::= { hsw2000c01v1Entry 53 }

		-- 1.3.6.1.4.1.10106.3.101291.1.1.55
		hsw2000c01v1FrzFailTim OBJECT-TYPE
			SYNTAX HswTiming
			MAX-ACCESS read-write
			STATUS current
			DESCRIPTION
				"Allows selecting the desired timing for the freeze fail"
		::= { hsw2000c01v1Entry 55 }

		-- 1.3.6.1.4.1.10106.3.101291.1.1.57
		hsw2000c01v1PatFailTim OBJECT-TYPE
			SYNTAX HswTiming
			MAX-ACCESS read-write
			STATUS current
			DESCRIPTION
				"Allows selecting the desired timing for the pattern fail"
		::= { hsw2000c01v1Entry 57 }

		-- 1.3.6.1.4.1.10106.3.101291.1.1.59
		hsw2000c01v1CrcFailTim OBJECT-TYPE
			SYNTAX HswTiming
			MAX-ACCESS read-write
			STATUS current
			DESCRIPTION
				"Allows selecting the desired timing for the EDH/CRC"
		::= { hsw2000c01v1Entry 59 }

		-- 1.3.6.1.4.1.10106.3.101291.1.1.61
		hsw2000c01v1SilFailTim OBJECT-TYPE
			SYNTAX HswTiming
			MAX-ACCESS read-write
			STATUS current
			DESCRIPTION
				"Allows selecting the desired timing for the audio silence fail"
		::= { hsw2000c01v1Entry 61 }

		-- 1.3.6.1.4.1.10106.3.101291.1.1.63
		hsw2000c01v1OvrFailTim OBJECT-TYPE
			SYNTAX HswTiming
			MAX-ACCESS read-write
			STATUS current
			DESCRIPTION
				"Allows selecting the desired timing for the audio overload fail"
		::= { hsw2000c01v1Entry 63 }

		-- 1.3.6.1.4.1.10106.3.101291.1.1.65
		hsw2000c01v1PhFailTim OBJECT-TYPE
			SYNTAX HswTiming
			MAX-ACCESS read-write
			STATUS current
			DESCRIPTION
				"Allows selecting the desired timing for the audio phase fail"
		::= { hsw2000c01v1Entry 65 }

		-- 1.3.6.1.4.1.10106.3.101291.1.1.67
		hsw2000c01v1PresFailTim OBJECT-TYPE
			SYNTAX HswTiming
			MAX-ACCESS read-write
			STATUS current
			DESCRIPTION
				"Allows selecting the desired timing for the audio presence fail"
		::= { hsw2000c01v1Entry 67 }

		-- 1.3.6.1.4.1.10106.3.101291.1.1.69
		hsw2000c01v1ActPer1 OBJECT-TYPE
			SYNTAX TimeS2
			MAX-ACCESS read-write
			STATUS current
			DESCRIPTION
				"Activation time used in timing 1"
		::= { hsw2000c01v1Entry 69 }

		-- 1.3.6.1.4.1.10106.3.101291.1.1.71
		hsw2000c01v1DeactPer1 OBJECT-TYPE
			SYNTAX TimeS2
			MAX-ACCESS read-write
			STATUS current
			DESCRIPTION
				"Deactivation time used in timing 1"
		::= { hsw2000c01v1Entry 71 }

		-- 1.3.6.1.4.1.10106.3.101291.1.1.73
		hsw2000c01v1ActPer2 OBJECT-TYPE
			SYNTAX TimeS2
			MAX-ACCESS read-write
			STATUS current
			DESCRIPTION
				"Activation time used in timing 2"
		::= { hsw2000c01v1Entry 73 }

		-- 1.3.6.1.4.1.10106.3.101291.1.1.75
		hsw2000c01v1DeactPer2 OBJECT-TYPE
			SYNTAX TimeS2
			MAX-ACCESS read-write
			STATUS current
			DESCRIPTION
				"Deactivation time used in timing 2"
		::= { hsw2000c01v1Entry 75 }

		-- 1.3.6.1.4.1.10106.3.101291.1.1.77
		hsw2000c01v1CrcThreshold OBJECT-TYPE
			SYNTAX Rate2
			MAX-ACCESS read-write
			STATUS current
			DESCRIPTION
				"Allows adjusting the threshold that activates the EDH/CRC fail"
		::= { hsw2000c01v1Entry 77 }

		-- 1.3.6.1.4.1.10106.3.101291.1.1.79
		hsw2000c01v1BlackThreshold OBJECT-TYPE
			SYNTAX BlackThreshold
			MAX-ACCESS read-write
			STATUS current
			DESCRIPTION
				"Allows adjusting the threshold thas activates the black fail"
		::= { hsw2000c01v1Entry 79 }

		-- 1.3.6.1.4.1.10106.3.101291.1.1.81
		hsw2000c01v1VertFrozenWin OBJECT-TYPE
			SYNTAX Rate1
			MAX-ACCESS read-write
			STATUS current
			DESCRIPTION
				"Allows adjusting the vertical size of the window used in the freeze detector"
		::= { hsw2000c01v1Entry 81 }

		-- 1.3.6.1.4.1.10106.3.101291.1.1.83
		hsw2000c01v1HtalFrozenWin OBJECT-TYPE
			SYNTAX Rate1
			MAX-ACCESS read-write
			STATUS current
			DESCRIPTION
				"Allows adjusting the horizontal size of the window used in the freeze detector"
		::= { hsw2000c01v1Entry 83 }

		-- 1.3.6.1.4.1.10106.3.101291.1.1.85
		hsw2000c01v1In1PhyFailMsk OBJECT-TYPE
			SYNTAX BitMask
			MAX-ACCESS read-write
			STATUS current
			DESCRIPTION
				"Allows masking the signal absence fail"
		::= { hsw2000c01v1Entry 85 }

		-- 1.3.6.1.4.1.10106.3.101291.1.1.87
		hsw2000c01v1In1FmtFailMsk OBJECT-TYPE
			SYNTAX BitMask
			MAX-ACCESS read-write
			STATUS current
			DESCRIPTION
				"Allows masking the format fail"
		::= { hsw2000c01v1Entry 87 }

		-- 1.3.6.1.4.1.10106.3.101291.1.1.89
		hsw2000c01v1In1IncFailMsk OBJECT-TYPE
			SYNTAX BitMask
			MAX-ACCESS read-write
			STATUS current
			DESCRIPTION
				"Allows masking the incompatible format fail"
		::= { hsw2000c01v1Entry 89 }

		-- 1.3.6.1.4.1.10106.3.101291.1.1.91
		hsw2000c01v1In1BlkFailMsk OBJECT-TYPE
			SYNTAX BitMask
			MAX-ACCESS read-write
			STATUS current
			DESCRIPTION
				"Allows masking the black signal fail"
		::= { hsw2000c01v1Entry 91 }

		-- 1.3.6.1.4.1.10106.3.101291.1.1.93
		hsw2000c01v1In1FrzFailMsk OBJECT-TYPE
			SYNTAX BitMask
			MAX-ACCESS read-write
			STATUS current
			DESCRIPTION
				"Allows masking the freeze signal fail"
		::= { hsw2000c01v1Entry 93 }

		-- 1.3.6.1.4.1.10106.3.101291.1.1.95
		hsw2000c01v1In1PatFailMsk OBJECT-TYPE
			SYNTAX BitMask
			MAX-ACCESS read-write
			STATUS current
			DESCRIPTION
				"Allows masking the video pattern fail"
		::= { hsw2000c01v1Entry 95 }

		-- 1.3.6.1.4.1.10106.3.101291.1.1.97
		hsw2000c01v1In1CrcFailMsk OBJECT-TYPE
			SYNTAX BitMask
			MAX-ACCESS read-write
			STATUS current
			DESCRIPTION
				"Allows masking the EDH/CRC"
		::= { hsw2000c01v1Entry 97 }

		-- 1.3.6.1.4.1.10106.3.101291.1.1.99
		hsw2000c01v1In1SilFailMsk OBJECT-TYPE
			SYNTAX BitMask
			MAX-ACCESS read-write
			STATUS current
			DESCRIPTION
				"Allows masking the audio silence fail"
		::= { hsw2000c01v1Entry 99 }

		-- 1.3.6.1.4.1.10106.3.101291.1.1.101
		hsw2000c01v1In1OvrFailMsk OBJECT-TYPE
			SYNTAX BitMask
			MAX-ACCESS read-write
			STATUS current
			DESCRIPTION
				"Allows masking the audio overload fail"
		::= { hsw2000c01v1Entry 101 }

		-- 1.3.6.1.4.1.10106.3.101291.1.1.103
		hsw2000c01v1In1PhFailMsk OBJECT-TYPE
			SYNTAX BitMask
			MAX-ACCESS read-write
			STATUS current
			DESCRIPTION
				"Allows masking the audio phase fail"
		::= { hsw2000c01v1Entry 103 }

		-- 1.3.6.1.4.1.10106.3.101291.1.1.105
		hsw2000c01v1In1PreFailMsk OBJECT-TYPE
			SYNTAX BitMask
			MAX-ACCESS read-write
			STATUS current
			DESCRIPTION
				"Allows masking the audio presence fail"
		::= { hsw2000c01v1Entry 105 }

		-- 1.3.6.1.4.1.10106.3.101291.1.1.107
		hsw2000c01v1In2PhyFailMsk OBJECT-TYPE
			SYNTAX BitMask
			MAX-ACCESS read-write
			STATUS current
			DESCRIPTION
				"Allows masking the signal absence fail"
		::= { hsw2000c01v1Entry 107 }

		-- 1.3.6.1.4.1.10106.3.101291.1.1.109
		hsw2000c01v1In2FmtFailMsk OBJECT-TYPE
			SYNTAX BitMask
			MAX-ACCESS read-write
			STATUS current
			DESCRIPTION
				"Allows masking the format fail"
		::= { hsw2000c01v1Entry 109 }

		-- 1.3.6.1.4.1.10106.3.101291.1.1.111
		hsw2000c01v1In2IncFailMsk OBJECT-TYPE
			SYNTAX BitMask
			MAX-ACCESS read-write
			STATUS current
			DESCRIPTION
				"Allows masking the incompatible format fail"
		::= { hsw2000c01v1Entry 111 }

		-- 1.3.6.1.4.1.10106.3.101291.1.1.113
		hsw2000c01v1In2BlkFailMsk OBJECT-TYPE
			SYNTAX BitMask
			MAX-ACCESS read-write
			STATUS current
			DESCRIPTION
				"Allows masking the black signal fail"
		::= { hsw2000c01v1Entry 113 }

		-- 1.3.6.1.4.1.10106.3.101291.1.1.115
		hsw2000c01v1In2FrzFailMsk OBJECT-TYPE
			SYNTAX BitMask
			MAX-ACCESS read-write
			STATUS current
			DESCRIPTION
				"Allows masking the freeze signal fail"
		::= { hsw2000c01v1Entry 115 }

		-- 1.3.6.1.4.1.10106.3.101291.1.1.117
		hsw2000c01v1In2PatFailMsk OBJECT-TYPE
			SYNTAX BitMask
			MAX-ACCESS read-write
			STATUS current
			DESCRIPTION
				"Allows masking the video pattern fail"
		::= { hsw2000c01v1Entry 117 }

		-- 1.3.6.1.4.1.10106.3.101291.1.1.119
		hsw2000c01v1In2CrcFailMsk OBJECT-TYPE
			SYNTAX BitMask
			MAX-ACCESS read-write
			STATUS current
			DESCRIPTION
				"Allows masking the EDH/CRC"
		::= { hsw2000c01v1Entry 119 }

		-- 1.3.6.1.4.1.10106.3.101291.1.1.121
		hsw2000c01v1In2SilFailMsk OBJECT-TYPE
			SYNTAX BitMask
			MAX-ACCESS read-write
			STATUS current
			DESCRIPTION
				"Allows masking the audio silence fail"
		::= { hsw2000c01v1Entry 121 }

		-- 1.3.6.1.4.1.10106.3.101291.1.1.123
		hsw2000c01v1In2OvrFailMsk OBJECT-TYPE
			SYNTAX BitMask
			MAX-ACCESS read-write
			STATUS current
			DESCRIPTION
				"Allows masking the audio overload fail"
		::= { hsw2000c01v1Entry 123 }

		-- 1.3.6.1.4.1.10106.3.101291.1.1.125
		hsw2000c01v1In2PhFailMsk OBJECT-TYPE
			SYNTAX BitMask
			MAX-ACCESS read-write
			STATUS current
			DESCRIPTION
				"Allows masking the audio phase fail"
		::= { hsw2000c01v1Entry 125 }

		-- 1.3.6.1.4.1.10106.3.101291.1.1.127
		hsw2000c01v1In2PreFailMsk OBJECT-TYPE
			SYNTAX BitMask
			MAX-ACCESS read-write
			STATUS current
			DESCRIPTION
				"Allows masking the audio presence fail"
		::= { hsw2000c01v1Entry 127 }

		-- 1.3.6.1.4.1.10106.3.101291.1.1.129
		hsw2000c01v1RefFailMsk OBJECT-TYPE
			SYNTAX BitMask
			MAX-ACCESS read-write
			STATUS current
			DESCRIPTION
				"Allows masking the reference absence fail"
		::= { hsw2000c01v1Entry 129 }

		-- 1.3.6.1.4.1.10106.3.101291.1.1.131
		hsw2000c01v1LockFailMsk OBJECT-TYPE
			SYNTAX BitMask
			MAX-ACCESS read-write
			STATUS current
			DESCRIPTION
				"Allows masking the reference unlock fail"
		::= { hsw2000c01v1Entry 131 }

		-- 1.3.6.1.4.1.10106.3.101291.1.1.133
		hsw2000c01v1In1AudG1p0Msk OBJECT-TYPE
			SYNTAX AudioMask
			MAX-ACCESS read-write
			STATUS current
			DESCRIPTION
				"Allows masking the audio in group 1 pair 0"
		::= { hsw2000c01v1Entry 133 }

		-- 1.3.6.1.4.1.10106.3.101291.1.1.135
		hsw2000c01v1In1AudG1p1Msk OBJECT-TYPE
			SYNTAX AudioMask
			MAX-ACCESS read-write
			STATUS current
			DESCRIPTION
				"Allows masking the audio in group 1 pair 1"
		::= { hsw2000c01v1Entry 135 }

		-- 1.3.6.1.4.1.10106.3.101291.1.1.137
		hsw2000c01v1In1AudG2p0Msk OBJECT-TYPE
			SYNTAX AudioMask
			MAX-ACCESS read-write
			STATUS current
			DESCRIPTION
				"Allows masking the audio in group 2 pair 0"
		::= { hsw2000c01v1Entry 137 }

		-- 1.3.6.1.4.1.10106.3.101291.1.1.139
		hsw2000c01v1In1AudG2p1Msk OBJECT-TYPE
			SYNTAX AudioMask
			MAX-ACCESS read-write
			STATUS current
			DESCRIPTION
				"Allows masking the audio in group 2 pair 1"
		::= { hsw2000c01v1Entry 139 }

		-- 1.3.6.1.4.1.10106.3.101291.1.1.141
		hsw2000c01v1In1AudG3p0Msk OBJECT-TYPE
			SYNTAX AudioMask
			MAX-ACCESS read-write
			STATUS current
			DESCRIPTION
				"Allows masking the audio in group 3 pair 0"
		::= { hsw2000c01v1Entry 141 }

		-- 1.3.6.1.4.1.10106.3.101291.1.1.143
		hsw2000c01v1In1AudG3p1Msk OBJECT-TYPE
			SYNTAX AudioMask
			MAX-ACCESS read-write
			STATUS current
			DESCRIPTION
				"Allows masking the audio in group 3 pair 1"
		::= { hsw2000c01v1Entry 143 }

		-- 1.3.6.1.4.1.10106.3.101291.1.1.145
		hsw2000c01v1In1AudG4p0Msk OBJECT-TYPE
			SYNTAX AudioMask
			MAX-ACCESS read-write
			STATUS current
			DESCRIPTION
				"Allows masking the audio in group 4 pair 0"
		::= { hsw2000c01v1Entry 145 }

		-- 1.3.6.1.4.1.10106.3.101291.1.1.147
		hsw2000c01v1In1AudG4p1Msk OBJECT-TYPE
			SYNTAX AudioMask
			MAX-ACCESS read-write
			STATUS current
			DESCRIPTION
				"Allows masking the audio in group 4 pair 1"
		::= { hsw2000c01v1Entry 147 }

		-- 1.3.6.1.4.1.10106.3.101291.1.1.149
		hsw2000c01v1In2AudG1p0Msk OBJECT-TYPE
			SYNTAX AudioMask
			MAX-ACCESS read-write
			STATUS current
			DESCRIPTION
				"Allows masking the audio in group 1 pair 0"
		::= { hsw2000c01v1Entry 149 }

		-- 1.3.6.1.4.1.10106.3.101291.1.1.151
		hsw2000c01v1In2AudG1p1Msk OBJECT-TYPE
			SYNTAX AudioMask
			MAX-ACCESS read-write
			STATUS current
			DESCRIPTION
				"Allows masking the audio in group 1 pair 1"
		::= { hsw2000c01v1Entry 151 }

		-- 1.3.6.1.4.1.10106.3.101291.1.1.153
		hsw2000c01v1In2AudG2p0Msk OBJECT-TYPE
			SYNTAX AudioMask
			MAX-ACCESS read-write
			STATUS current
			DESCRIPTION
				"Allows masking the audio in group 2 pair 0"
		::= { hsw2000c01v1Entry 153 }

		-- 1.3.6.1.4.1.10106.3.101291.1.1.155
		hsw2000c01v1In2AudG2p1Msk OBJECT-TYPE
			SYNTAX AudioMask
			MAX-ACCESS read-write
			STATUS current
			DESCRIPTION
				"Allows masking the audio in group 2 pair 1"
		::= { hsw2000c01v1Entry 155 }

		-- 1.3.6.1.4.1.10106.3.101291.1.1.157
		hsw2000c01v1In2AudG3p0Msk OBJECT-TYPE
			SYNTAX AudioMask
			MAX-ACCESS read-write
			STATUS current
			DESCRIPTION
				"Allows masking the audio in group 3 pair 0"
		::= { hsw2000c01v1Entry 157 }

		-- 1.3.6.1.4.1.10106.3.101291.1.1.159
		hsw2000c01v1In2AudG3p1Msk OBJECT-TYPE
			SYNTAX AudioMask
			MAX-ACCESS read-write
			STATUS current
			DESCRIPTION
				"Allows masking the audio in group 3 pair 1"
		::= { hsw2000c01v1Entry 159 }

		-- 1.3.6.1.4.1.10106.3.101291.1.1.161
		hsw2000c01v1In2AudG4p0Msk OBJECT-TYPE
			SYNTAX AudioMask
			MAX-ACCESS read-write
			STATUS current
			DESCRIPTION
				"Allows masking the audio in group 4 pair 0"
		::= { hsw2000c01v1Entry 161 }

		-- 1.3.6.1.4.1.10106.3.101291.1.1.163
		hsw2000c01v1In2AudG4p1Msk OBJECT-TYPE
			SYNTAX AudioMask
			MAX-ACCESS read-write
			STATUS current
			DESCRIPTION
				"Allows masking the audio in group 4 pair 1"
		::= { hsw2000c01v1Entry 163 }

		-- 1.3.6.1.4.1.10106.3.101291.1.1.165
		hsw2000c01v1FrzToBckTime OBJECT-TYPE
			SYNTAX TimeS2
			MAX-ACCESS read-write
			STATUS current
			DESCRIPTION
				"Freeze to black timeout"
		::= { hsw2000c01v1Entry 165 }

		-- 1.3.6.1.4.1.10106.3.101291.1.1.167
		hsw2000c01v1SilenceLevel OBJECT-TYPE
			SYNTAX LevelDbfs3
			MAX-ACCESS read-write
			STATUS current
			DESCRIPTION
				"Allows adjusting the threshold level for the silence detector"
		::= { hsw2000c01v1Entry 167 }

		-- 1.3.6.1.4.1.10106.3.101291.1.1.169
		hsw2000c01v1SilenceTime OBJECT-TYPE
			SYNTAX TimeS2
			MAX-ACCESS read-write
			STATUS current
			DESCRIPTION
				"Allows adjusting the time for the silence detector"
		::= { hsw2000c01v1Entry 169 }

		-- 1.3.6.1.4.1.10106.3.101291.1.1.171
		hsw2000c01v1OverloadLevel OBJECT-TYPE
			SYNTAX LevelDbfs4
			MAX-ACCESS read-write
			STATUS current
			DESCRIPTION
				"Allows adjusting the threshold level for the overload detector"
		::= { hsw2000c01v1Entry 171 }

		-- 1.3.6.1.4.1.10106.3.101291.1.1.173
		hsw2000c01v1TxtLinesThrs OBJECT-TYPE
			SYNTAX TxtThreshold
			MAX-ACCESS read-write
			STATUS current
			DESCRIPTION
				"Low teletext line number threshold"
		::= { hsw2000c01v1Entry 173 }

		-- 1.3.6.1.4.1.10106.3.101291.1.1.175
		hsw2000c01v1In1Fail OBJECT-TYPE
			SYNTAX BitFail
			MAX-ACCESS read-only
			STATUS current
			DESCRIPTION
				"Input 1 fail"
		::= { hsw2000c01v1Entry 175 }

		-- 1.3.6.1.4.1.10106.3.101291.1.1.176
		hsw2000c01v1In1FailTrapEnable OBJECT-TYPE
			SYNTAX AlarmEnable
			MAX-ACCESS read-write
			STATUS current
			DESCRIPTION
				"Input 1 fail Trap Enable"
		::= { hsw2000c01v1Entry 176 }

		-- 1.3.6.1.4.1.10106.3.101291.1.1.177
		hsw2000c01v1In2Fail OBJECT-TYPE
			SYNTAX BitFail
			MAX-ACCESS read-only
			STATUS current
			DESCRIPTION
				"Input 2 fail"
		::= { hsw2000c01v1Entry 177 }

		-- 1.3.6.1.4.1.10106.3.101291.1.1.178
		hsw2000c01v1In2FailTrapEnable OBJECT-TYPE
			SYNTAX AlarmEnable
			MAX-ACCESS read-write
			STATUS current
			DESCRIPTION
				"Input 2 fail Trap Enable"
		::= { hsw2000c01v1Entry 178 }

		-- 1.3.6.1.4.1.10106.3.101291.1.1.179
		hsw2000c01v1EqualPid OBJECT-TYPE
			SYNTAX UmidStatus
			MAX-ACCESS read-only
			STATUS current
			DESCRIPTION
				"Indicates if both  inputs have same PID"
		::= { hsw2000c01v1Entry 179 }

		-- 1.3.6.1.4.1.10106.3.101291.1.1.180
		hsw2000c01v1EqualPidTrapEnable OBJECT-TYPE
			SYNTAX AlarmEnable
			MAX-ACCESS read-write
			STATUS current
			DESCRIPTION
				"Indicates if both  inputs have same PID Trap Enable"
		::= { hsw2000c01v1Entry 180 }

		-- 1.3.6.1.4.1.10106.3.101291.1.1.181
		hsw2000c01v1SelOut1 OBJECT-TYPE
			SYNTAX HswOutput
			MAX-ACCESS read-only
			STATUS current
			DESCRIPTION
				"Output 1"
		::= { hsw2000c01v1Entry 181 }

		-- 1.3.6.1.4.1.10106.3.101291.1.1.182
		hsw2000c01v1SelOut1TrapEnable OBJECT-TYPE
			SYNTAX AlarmEnable
			MAX-ACCESS read-write
			STATUS current
			DESCRIPTION
				"Output 1 Trap Enable"
		::= { hsw2000c01v1Entry 182 }

		-- 1.3.6.1.4.1.10106.3.101291.1.1.183
		hsw2000c01v1SelOut2 OBJECT-TYPE
			SYNTAX HswOutput
			MAX-ACCESS read-only
			STATUS current
			DESCRIPTION
				"Output 2"
		::= { hsw2000c01v1Entry 183 }

		-- 1.3.6.1.4.1.10106.3.101291.1.1.184
		hsw2000c01v1SelOut2TrapEnable OBJECT-TYPE
			SYNTAX AlarmEnable
			MAX-ACCESS read-write
			STATUS current
			DESCRIPTION
				"Output 2 Trap Enable"
		::= { hsw2000c01v1Entry 184 }

		-- 1.3.6.1.4.1.10106.3.101291.1.1.185
		hsw2000c01v1EqualUmid OBJECT-TYPE
			SYNTAX UmidStatus
			MAX-ACCESS read-only
			STATUS current
			DESCRIPTION
				"Indicates if both  inputs have same UMID"
		::= { hsw2000c01v1Entry 185 }

		-- 1.3.6.1.4.1.10106.3.101291.1.1.186
		hsw2000c01v1EqualUmidTrapEnable OBJECT-TYPE
			SYNTAX AlarmEnable
			MAX-ACCESS read-write
			STATUS current
			DESCRIPTION
				"Indicates if both  inputs have same UMID Trap Enable"
		::= { hsw2000c01v1Entry 186 }

		-- 1.3.6.1.4.1.10106.3.101291.1.1.187
		hsw2000c01v1In1PhyFail OBJECT-TYPE
			SYNTAX BitFail
			MAX-ACCESS read-only
			STATUS current
			DESCRIPTION
				"Absence fail"
		::= { hsw2000c01v1Entry 187 }

		-- 1.3.6.1.4.1.10106.3.101291.1.1.188
		hsw2000c01v1In1PhyFailTrapEnable OBJECT-TYPE
			SYNTAX AlarmEnable
			MAX-ACCESS read-write
			STATUS current
			DESCRIPTION
				"Absence fail Trap Enable"
		::= { hsw2000c01v1Entry 188 }

		-- 1.3.6.1.4.1.10106.3.101291.1.1.189
		hsw2000c01v1In1FmtFail OBJECT-TYPE
			SYNTAX BitFail
			MAX-ACCESS read-only
			STATUS current
			DESCRIPTION
				"Format fail"
		::= { hsw2000c01v1Entry 189 }

		-- 1.3.6.1.4.1.10106.3.101291.1.1.190
		hsw2000c01v1In1FmtFailTrapEnable OBJECT-TYPE
			SYNTAX AlarmEnable
			MAX-ACCESS read-write
			STATUS current
			DESCRIPTION
				"Format fail Trap Enable"
		::= { hsw2000c01v1Entry 190 }

		-- 1.3.6.1.4.1.10106.3.101291.1.1.191
		hsw2000c01v1In1IncFail OBJECT-TYPE
			SYNTAX BitFail
			MAX-ACCESS read-only
			STATUS current
			DESCRIPTION
				"Incompatible format fail"
		::= { hsw2000c01v1Entry 191 }

		-- 1.3.6.1.4.1.10106.3.101291.1.1.192
		hsw2000c01v1In1IncFailTrapEnable OBJECT-TYPE
			SYNTAX AlarmEnable
			MAX-ACCESS read-write
			STATUS current
			DESCRIPTION
				"Incompatible format fail Trap Enable"
		::= { hsw2000c01v1Entry 192 }

		-- 1.3.6.1.4.1.10106.3.101291.1.1.193
		hsw2000c01v1In1BlkFail OBJECT-TYPE
			SYNTAX BitFail
			MAX-ACCESS read-only
			STATUS current
			DESCRIPTION
				"Black signal fail"
		::= { hsw2000c01v1Entry 193 }

		-- 1.3.6.1.4.1.10106.3.101291.1.1.194
		hsw2000c01v1In1BlkFailTrapEnable OBJECT-TYPE
			SYNTAX AlarmEnable
			MAX-ACCESS read-write
			STATUS current
			DESCRIPTION
				"Black signal fail Trap Enable"
		::= { hsw2000c01v1Entry 194 }

		-- 1.3.6.1.4.1.10106.3.101291.1.1.195
		hsw2000c01v1In1FrzFail OBJECT-TYPE
			SYNTAX BitFail
			MAX-ACCESS read-only
			STATUS current
			DESCRIPTION
				"Freeze signal fail"
		::= { hsw2000c01v1Entry 195 }

		-- 1.3.6.1.4.1.10106.3.101291.1.1.196
		hsw2000c01v1In1FrzFailTrapEnable OBJECT-TYPE
			SYNTAX AlarmEnable
			MAX-ACCESS read-write
			STATUS current
			DESCRIPTION
				"Freeze signal fail Trap Enable"
		::= { hsw2000c01v1Entry 196 }

		-- 1.3.6.1.4.1.10106.3.101291.1.1.197
		hsw2000c01v1In1PatFail OBJECT-TYPE
			SYNTAX BitFail
			MAX-ACCESS read-only
			STATUS current
			DESCRIPTION
				"Video pattern fail"
		::= { hsw2000c01v1Entry 197 }

		-- 1.3.6.1.4.1.10106.3.101291.1.1.198
		hsw2000c01v1In1PatFailTrapEnable OBJECT-TYPE
			SYNTAX AlarmEnable
			MAX-ACCESS read-write
			STATUS current
			DESCRIPTION
				"Video pattern fail Trap Enable"
		::= { hsw2000c01v1Entry 198 }

		-- 1.3.6.1.4.1.10106.3.101291.1.1.199
		hsw2000c01v1In1CrcFail OBJECT-TYPE
			SYNTAX BitFail
			MAX-ACCESS read-only
			STATUS current
			DESCRIPTION
				"EDH/CRC fail"
		::= { hsw2000c01v1Entry 199 }

		-- 1.3.6.1.4.1.10106.3.101291.1.1.200
		hsw2000c01v1In1CrcFailTrapEnable OBJECT-TYPE
			SYNTAX AlarmEnable
			MAX-ACCESS read-write
			STATUS current
			DESCRIPTION
				"EDH/CRC fail Trap Enable"
		::= { hsw2000c01v1Entry 200 }

		-- 1.3.6.1.4.1.10106.3.101291.1.1.201
		hsw2000c01v1In1SilFail OBJECT-TYPE
			SYNTAX BitFail
			MAX-ACCESS read-only
			STATUS current
			DESCRIPTION
				"Audio silence fail"
		::= { hsw2000c01v1Entry 201 }

		-- 1.3.6.1.4.1.10106.3.101291.1.1.202
		hsw2000c01v1In1SilFailTrapEnable OBJECT-TYPE
			SYNTAX AlarmEnable
			MAX-ACCESS read-write
			STATUS current
			DESCRIPTION
				"Audio silence fail Trap Enable"
		::= { hsw2000c01v1Entry 202 }

		-- 1.3.6.1.4.1.10106.3.101291.1.1.203
		hsw2000c01v1In1OvrFail OBJECT-TYPE
			SYNTAX BitFail
			MAX-ACCESS read-only
			STATUS current
			DESCRIPTION
				"Audio overload fail"
		::= { hsw2000c01v1Entry 203 }

		-- 1.3.6.1.4.1.10106.3.101291.1.1.204
		hsw2000c01v1In1OvrFailTrapEnable OBJECT-TYPE
			SYNTAX AlarmEnable
			MAX-ACCESS read-write
			STATUS current
			DESCRIPTION
				"Audio overload fail Trap Enable"
		::= { hsw2000c01v1Entry 204 }

		-- 1.3.6.1.4.1.10106.3.101291.1.1.205
		hsw2000c01v1In1PhFail OBJECT-TYPE
			SYNTAX BitFail
			MAX-ACCESS read-only
			STATUS current
			DESCRIPTION
				"Audio phase fail"
		::= { hsw2000c01v1Entry 205 }

		-- 1.3.6.1.4.1.10106.3.101291.1.1.206
		hsw2000c01v1In1PhFailTrapEnable OBJECT-TYPE
			SYNTAX AlarmEnable
			MAX-ACCESS read-write
			STATUS current
			DESCRIPTION
				"Audio phase fail Trap Enable"
		::= { hsw2000c01v1Entry 206 }

		-- 1.3.6.1.4.1.10106.3.101291.1.1.207
		hsw2000c01v1In1PreFail OBJECT-TYPE
			SYNTAX BitFail
			MAX-ACCESS read-only
			STATUS current
			DESCRIPTION
				"Audio presence fail"
		::= { hsw2000c01v1Entry 207 }

		-- 1.3.6.1.4.1.10106.3.101291.1.1.208
		hsw2000c01v1In1PreFailTrapEnable OBJECT-TYPE
			SYNTAX AlarmEnable
			MAX-ACCESS read-write
			STATUS current
			DESCRIPTION
				"Audio presence fail Trap Enable"
		::= { hsw2000c01v1Entry 208 }

		-- 1.3.6.1.4.1.10106.3.101291.1.1.209
		hsw2000c01v1In2PhyFail OBJECT-TYPE
			SYNTAX BitFail
			MAX-ACCESS read-only
			STATUS current
			DESCRIPTION
				"Absence fail"
		::= { hsw2000c01v1Entry 209 }

		-- 1.3.6.1.4.1.10106.3.101291.1.1.210
		hsw2000c01v1In2PhyFailTrapEnable OBJECT-TYPE
			SYNTAX AlarmEnable
			MAX-ACCESS read-write
			STATUS current
			DESCRIPTION
				"Absence fail Trap Enable"
		::= { hsw2000c01v1Entry 210 }

		-- 1.3.6.1.4.1.10106.3.101291.1.1.211
		hsw2000c01v1In2FmtFail OBJECT-TYPE
			SYNTAX BitFail
			MAX-ACCESS read-only
			STATUS current
			DESCRIPTION
				"Format fail"
		::= { hsw2000c01v1Entry 211 }

		-- 1.3.6.1.4.1.10106.3.101291.1.1.212
		hsw2000c01v1In2FmtFailTrapEnable OBJECT-TYPE
			SYNTAX AlarmEnable
			MAX-ACCESS read-write
			STATUS current
			DESCRIPTION
				"Format fail Trap Enable"
		::= { hsw2000c01v1Entry 212 }

		-- 1.3.6.1.4.1.10106.3.101291.1.1.213
		hsw2000c01v1In2IncFail OBJECT-TYPE
			SYNTAX BitFail
			MAX-ACCESS read-only
			STATUS current
			DESCRIPTION
				"Incompatible format fail"
		::= { hsw2000c01v1Entry 213 }

		-- 1.3.6.1.4.1.10106.3.101291.1.1.214
		hsw2000c01v1In2IncFailTrapEnable OBJECT-TYPE
			SYNTAX AlarmEnable
			MAX-ACCESS read-write
			STATUS current
			DESCRIPTION
				"Incompatible format fail Trap Enable"
		::= { hsw2000c01v1Entry 214 }

		-- 1.3.6.1.4.1.10106.3.101291.1.1.215
		hsw2000c01v1In2BlkFail OBJECT-TYPE
			SYNTAX BitFail
			MAX-ACCESS read-only
			STATUS current
			DESCRIPTION
				"Black signal fail"
		::= { hsw2000c01v1Entry 215 }

		-- 1.3.6.1.4.1.10106.3.101291.1.1.216
		hsw2000c01v1In2BlkFailTrapEnable OBJECT-TYPE
			SYNTAX AlarmEnable
			MAX-ACCESS read-write
			STATUS current
			DESCRIPTION
				"Black signal fail Trap Enable"
		::= { hsw2000c01v1Entry 216 }

		-- 1.3.6.1.4.1.10106.3.101291.1.1.217
		hsw2000c01v1In2FrzFail OBJECT-TYPE
			SYNTAX BitFail
			MAX-ACCESS read-only
			STATUS current
			DESCRIPTION
				"Freeze signal fail"
		::= { hsw2000c01v1Entry 217 }

		-- 1.3.6.1.4.1.10106.3.101291.1.1.218
		hsw2000c01v1In2FrzFailTrapEnable OBJECT-TYPE
			SYNTAX AlarmEnable
			MAX-ACCESS read-write
			STATUS current
			DESCRIPTION
				"Freeze signal fail Trap Enable"
		::= { hsw2000c01v1Entry 218 }

		-- 1.3.6.1.4.1.10106.3.101291.1.1.219
		hsw2000c01v1In2PatFail OBJECT-TYPE
			SYNTAX BitFail
			MAX-ACCESS read-only
			STATUS current
			DESCRIPTION
				"Video pattern fail"
		::= { hsw2000c01v1Entry 219 }

		-- 1.3.6.1.4.1.10106.3.101291.1.1.220
		hsw2000c01v1In2PatFailTrapEnable OBJECT-TYPE
			SYNTAX AlarmEnable
			MAX-ACCESS read-write
			STATUS current
			DESCRIPTION
				"Video pattern fail Trap Enable"
		::= { hsw2000c01v1Entry 220 }

		-- 1.3.6.1.4.1.10106.3.101291.1.1.221
		hsw2000c01v1In2CrcFail OBJECT-TYPE
			SYNTAX BitFail
			MAX-ACCESS read-only
			STATUS current
			DESCRIPTION
				"EDH/CRC fail"
		::= { hsw2000c01v1Entry 221 }

		-- 1.3.6.1.4.1.10106.3.101291.1.1.222
		hsw2000c01v1In2CrcFailTrapEnable OBJECT-TYPE
			SYNTAX AlarmEnable
			MAX-ACCESS read-write
			STATUS current
			DESCRIPTION
				"EDH/CRC fail Trap Enable"
		::= { hsw2000c01v1Entry 222 }

		-- 1.3.6.1.4.1.10106.3.101291.1.1.223
		hsw2000c01v1In2SilFail OBJECT-TYPE
			SYNTAX BitFail
			MAX-ACCESS read-only
			STATUS current
			DESCRIPTION
				"Audio silence fail"
		::= { hsw2000c01v1Entry 223 }

		-- 1.3.6.1.4.1.10106.3.101291.1.1.224
		hsw2000c01v1In2SilFailTrapEnable OBJECT-TYPE
			SYNTAX AlarmEnable
			MAX-ACCESS read-write
			STATUS current
			DESCRIPTION
				"Audio silence fail Trap Enable"
		::= { hsw2000c01v1Entry 224 }

		-- 1.3.6.1.4.1.10106.3.101291.1.1.225
		hsw2000c01v1In2OvrFail OBJECT-TYPE
			SYNTAX BitFail
			MAX-ACCESS read-only
			STATUS current
			DESCRIPTION
				"Audio overload fail"
		::= { hsw2000c01v1Entry 225 }

		-- 1.3.6.1.4.1.10106.3.101291.1.1.226
		hsw2000c01v1In2OvrFailTrapEnable OBJECT-TYPE
			SYNTAX AlarmEnable
			MAX-ACCESS read-write
			STATUS current
			DESCRIPTION
				"Audio overload fail Trap Enable"
		::= { hsw2000c01v1Entry 226 }

		-- 1.3.6.1.4.1.10106.3.101291.1.1.227
		hsw2000c01v1In2PhFail OBJECT-TYPE
			SYNTAX BitFail
			MAX-ACCESS read-only
			STATUS current
			DESCRIPTION
				"Audio phase fail"
		::= { hsw2000c01v1Entry 227 }

		-- 1.3.6.1.4.1.10106.3.101291.1.1.228
		hsw2000c01v1In2PhFailTrapEnable OBJECT-TYPE
			SYNTAX AlarmEnable
			MAX-ACCESS read-write
			STATUS current
			DESCRIPTION
				"Audio phase fail Trap Enable"
		::= { hsw2000c01v1Entry 228 }

		-- 1.3.6.1.4.1.10106.3.101291.1.1.229
		hsw2000c01v1In2PreFail OBJECT-TYPE
			SYNTAX BitFail
			MAX-ACCESS read-only
			STATUS current
			DESCRIPTION
				"Audio presence fail"
		::= { hsw2000c01v1Entry 229 }

		-- 1.3.6.1.4.1.10106.3.101291.1.1.230
		hsw2000c01v1In2PreFailTrapEnable OBJECT-TYPE
			SYNTAX AlarmEnable
			MAX-ACCESS read-write
			STATUS current
			DESCRIPTION
				"Audio presence fail Trap Enable"
		::= { hsw2000c01v1Entry 230 }

		-- 1.3.6.1.4.1.10106.3.101291.1.1.231
		hsw2000c01v1RefFail OBJECT-TYPE
			SYNTAX BitFail
			MAX-ACCESS read-only
			STATUS current
			DESCRIPTION
				"Reference absence fail"
		::= { hsw2000c01v1Entry 231 }

		-- 1.3.6.1.4.1.10106.3.101291.1.1.232
		hsw2000c01v1RefFailTrapEnable OBJECT-TYPE
			SYNTAX AlarmEnable
			MAX-ACCESS read-write
			STATUS current
			DESCRIPTION
				"Reference absence fail Trap Enable"
		::= { hsw2000c01v1Entry 232 }

		-- 1.3.6.1.4.1.10106.3.101291.1.1.233
		hsw2000c01v1LockFail OBJECT-TYPE
			SYNTAX BitFail
			MAX-ACCESS read-only
			STATUS current
			DESCRIPTION
				"Reference unlock fail"
		::= { hsw2000c01v1Entry 233 }

		-- 1.3.6.1.4.1.10106.3.101291.1.1.234
		hsw2000c01v1LockFailTrapEnable OBJECT-TYPE
			SYNTAX AlarmEnable
			MAX-ACCESS read-write
			STATUS current
			DESCRIPTION
				"Reference unlock fail Trap Enable"
		::= { hsw2000c01v1Entry 234 }

		-- 1.3.6.1.4.1.10106.3.101291.1.1.235
		hsw2000c01v1In1Format OBJECT-TYPE
			SYNTAX SdiHd3gFmt3
			MAX-ACCESS read-only
			STATUS current
			DESCRIPTION
				"Input format"
		::= { hsw2000c01v1Entry 235 }

		-- 1.3.6.1.4.1.10106.3.101291.1.1.236
		hsw2000c01v1In1FormatTrapEnable OBJECT-TYPE
			SYNTAX AlarmEnable
			MAX-ACCESS read-write
			STATUS current
			DESCRIPTION
				"Input format Trap Enable"
		::= { hsw2000c01v1Entry 236 }

		-- 1.3.6.1.4.1.10106.3.101291.1.1.237
		hsw2000c01v1In2Format OBJECT-TYPE
			SYNTAX SdiHd3gFmt3
			MAX-ACCESS read-only
			STATUS current
			DESCRIPTION
				"Input format"
		::= { hsw2000c01v1Entry 237 }

		-- 1.3.6.1.4.1.10106.3.101291.1.1.238
		hsw2000c01v1In2FormatTrapEnable OBJECT-TYPE
			SYNTAX AlarmEnable
			MAX-ACCESS read-write
			STATUS current
			DESCRIPTION
				"Input format Trap Enable"
		::= { hsw2000c01v1Entry 238 }

		-- 1.3.6.1.4.1.10106.3.101291.1.1.239
		hsw2000c01v1RefFormat OBJECT-TYPE
			SYNTAX SdiHd3gFmt3
			MAX-ACCESS read-only
			STATUS current
			DESCRIPTION
				"Reference format"
		::= { hsw2000c01v1Entry 239 }

		-- 1.3.6.1.4.1.10106.3.101291.1.1.240
		hsw2000c01v1RefFormatTrapEnable OBJECT-TYPE
			SYNTAX AlarmEnable
			MAX-ACCESS read-write
			STATUS current
			DESCRIPTION
				"Reference format Trap Enable"
		::= { hsw2000c01v1Entry 240 }

		-- 1.3.6.1.4.1.10106.3.101291.1.1.241
		hsw2000c01v1In1PidPres OBJECT-TYPE
			SYNTAX Bit0No1Yes
			MAX-ACCESS read-only
			STATUS current
			DESCRIPTION
				"Indicates if there are PID packets"
		::= { hsw2000c01v1Entry 241 }

		-- 1.3.6.1.4.1.10106.3.101291.1.1.243
		hsw2000c01v1In2PidPres OBJECT-TYPE
			SYNTAX Bit0No1Yes
			MAX-ACCESS read-only
			STATUS current
			DESCRIPTION
				"Indicates if there are PID packets"
		::= { hsw2000c01v1Entry 243 }

		-- 1.3.6.1.4.1.10106.3.101291.1.1.245
		hsw2000c01v1In1UmidPres OBJECT-TYPE
			SYNTAX Bit0No1Yes
			MAX-ACCESS read-only
			STATUS current
			DESCRIPTION
				"Indicates if there are UMID packets"
		::= { hsw2000c01v1Entry 245 }

		-- 1.3.6.1.4.1.10106.3.101291.1.1.247
		hsw2000c01v1In2UmidPres OBJECT-TYPE
			SYNTAX Bit0No1Yes
			MAX-ACCESS read-only
			STATUS current
			DESCRIPTION
				"Indicates if there are UMID packets"
		::= { hsw2000c01v1Entry 247 }

		-- 1.3.6.1.4.1.10106.3.101291.1.1.249
		hsw2000c01v1In1Grp1Pres OBJECT-TYPE
			SYNTAX Bit0No1Yes
			MAX-ACCESS read-only
			STATUS current
			DESCRIPTION
				"Audio group 1 packet presence"
		::= { hsw2000c01v1Entry 249 }

		-- 1.3.6.1.4.1.10106.3.101291.1.1.250
		hsw2000c01v1In1Grp1PresTrapEnable OBJECT-TYPE
			SYNTAX AlarmEnable
			MAX-ACCESS read-write
			STATUS current
			DESCRIPTION
				"Audio group 1 packet presence Trap Enable"
		::= { hsw2000c01v1Entry 250 }

		-- 1.3.6.1.4.1.10106.3.101291.1.1.251
		hsw2000c01v1In1Grp2Pres OBJECT-TYPE
			SYNTAX Bit0No1Yes
			MAX-ACCESS read-only
			STATUS current
			DESCRIPTION
				"Audio group 2 packet presence"
		::= { hsw2000c01v1Entry 251 }

		-- 1.3.6.1.4.1.10106.3.101291.1.1.252
		hsw2000c01v1In1Grp2PresTrapEnable OBJECT-TYPE
			SYNTAX AlarmEnable
			MAX-ACCESS read-write
			STATUS current
			DESCRIPTION
				"Audio group 2 packet presence Trap Enable"
		::= { hsw2000c01v1Entry 252 }

		-- 1.3.6.1.4.1.10106.3.101291.1.1.253
		hsw2000c01v1In1Grp3Pres OBJECT-TYPE
			SYNTAX Bit0No1Yes
			MAX-ACCESS read-only
			STATUS current
			DESCRIPTION
				"Audio group 3 packet presence"
		::= { hsw2000c01v1Entry 253 }

		-- 1.3.6.1.4.1.10106.3.101291.1.1.254
		hsw2000c01v1In1Grp3PresTrapEnable OBJECT-TYPE
			SYNTAX AlarmEnable
			MAX-ACCESS read-write
			STATUS current
			DESCRIPTION
				"Audio group 3 packet presence Trap Enable"
		::= { hsw2000c01v1Entry 254 }

		-- 1.3.6.1.4.1.10106.3.101291.1.1.255
		hsw2000c01v1In1Grp4Pres OBJECT-TYPE
			SYNTAX Bit0No1Yes
			MAX-ACCESS read-only
			STATUS current
			DESCRIPTION
				"Audio group 4 packet presence"
		::= { hsw2000c01v1Entry 255 }

		-- 1.3.6.1.4.1.10106.3.101291.1.1.256
		hsw2000c01v1In1Grp4PresTrapEnable OBJECT-TYPE
			SYNTAX AlarmEnable
			MAX-ACCESS read-write
			STATUS current
			DESCRIPTION
				"Audio group 4 packet presence Trap Enable"
		::= { hsw2000c01v1Entry 256 }

		-- 1.3.6.1.4.1.10106.3.101291.1.1.257
		hsw2000c01v1In1Grp1P0Stat OBJECT-TYPE
			SYNTAX AudioStatus
			MAX-ACCESS read-only
			STATUS current
			DESCRIPTION
				"Audio group 1 pair 0 status"
		::= { hsw2000c01v1Entry 257 }

		-- 1.3.6.1.4.1.10106.3.101291.1.1.258
		hsw2000c01v1In1Grp1P0StatTrapEnable OBJECT-TYPE
			SYNTAX AlarmEnable
			MAX-ACCESS read-write
			STATUS current
			DESCRIPTION
				"Audio group 1 pair 0 status Trap Enable"
		::= { hsw2000c01v1Entry 258 }

		-- 1.3.6.1.4.1.10106.3.101291.1.1.259
		hsw2000c01v1In1Grp1P1Stat OBJECT-TYPE
			SYNTAX AudioStatus
			MAX-ACCESS read-only
			STATUS current
			DESCRIPTION
				"Audio group 1 pair 1 status"
		::= { hsw2000c01v1Entry 259 }

		-- 1.3.6.1.4.1.10106.3.101291.1.1.260
		hsw2000c01v1In1Grp1P1StatTrapEnable OBJECT-TYPE
			SYNTAX AlarmEnable
			MAX-ACCESS read-write
			STATUS current
			DESCRIPTION
				"Audio group 1 pair 1 status Trap Enable"
		::= { hsw2000c01v1Entry 260 }

		-- 1.3.6.1.4.1.10106.3.101291.1.1.261
		hsw2000c01v1In1Grp2P0Stat OBJECT-TYPE
			SYNTAX AudioStatus
			MAX-ACCESS read-only
			STATUS current
			DESCRIPTION
				"Audio group 2 pair 0 status"
		::= { hsw2000c01v1Entry 261 }

		-- 1.3.6.1.4.1.10106.3.101291.1.1.262
		hsw2000c01v1In1Grp2P0StatTrapEnable OBJECT-TYPE
			SYNTAX AlarmEnable
			MAX-ACCESS read-write
			STATUS current
			DESCRIPTION
				"Audio group 2 pair 0 status Trap Enable"
		::= { hsw2000c01v1Entry 262 }

		-- 1.3.6.1.4.1.10106.3.101291.1.1.263
		hsw2000c01v1In1Grp2P1Stat OBJECT-TYPE
			SYNTAX AudioStatus
			MAX-ACCESS read-only
			STATUS current
			DESCRIPTION
				"Audio group 2 pair 1 status"
		::= { hsw2000c01v1Entry 263 }

		-- 1.3.6.1.4.1.10106.3.101291.1.1.264
		hsw2000c01v1In1Grp2P1StatTrapEnable OBJECT-TYPE
			SYNTAX AlarmEnable
			MAX-ACCESS read-write
			STATUS current
			DESCRIPTION
				"Audio group 2 pair 1 status Trap Enable"
		::= { hsw2000c01v1Entry 264 }

		-- 1.3.6.1.4.1.10106.3.101291.1.1.265
		hsw2000c01v1In1Grp3P0Stat OBJECT-TYPE
			SYNTAX AudioStatus
			MAX-ACCESS read-only
			STATUS current
			DESCRIPTION
				"Audio group 3 pair 0 status"
		::= { hsw2000c01v1Entry 265 }

		-- 1.3.6.1.4.1.10106.3.101291.1.1.266
		hsw2000c01v1In1Grp3P0StatTrapEnable OBJECT-TYPE
			SYNTAX AlarmEnable
			MAX-ACCESS read-write
			STATUS current
			DESCRIPTION
				"Audio group 3 pair 0 status Trap Enable"
		::= { hsw2000c01v1Entry 266 }

		-- 1.3.6.1.4.1.10106.3.101291.1.1.267
		hsw2000c01v1In1Grp3P1Stat OBJECT-TYPE
			SYNTAX AudioStatus
			MAX-ACCESS read-only
			STATUS current
			DESCRIPTION
				"Audio group 3 pair 1 status"
		::= { hsw2000c01v1Entry 267 }

		-- 1.3.6.1.4.1.10106.3.101291.1.1.268
		hsw2000c01v1In1Grp3P1StatTrapEnable OBJECT-TYPE
			SYNTAX AlarmEnable
			MAX-ACCESS read-write
			STATUS current
			DESCRIPTION
				"Audio group 3 pair 1 status Trap Enable"
		::= { hsw2000c01v1Entry 268 }

		-- 1.3.6.1.4.1.10106.3.101291.1.1.269
		hsw2000c01v1In1Grp4P0Stat OBJECT-TYPE
			SYNTAX AudioStatus
			MAX-ACCESS read-only
			STATUS current
			DESCRIPTION
				"Audio group 4 pair 0 status"
		::= { hsw2000c01v1Entry 269 }

		-- 1.3.6.1.4.1.10106.3.101291.1.1.270
		hsw2000c01v1In1Grp4P0StatTrapEnable OBJECT-TYPE
			SYNTAX AlarmEnable
			MAX-ACCESS read-write
			STATUS current
			DESCRIPTION
				"Audio group 4 pair 0 status Trap Enable"
		::= { hsw2000c01v1Entry 270 }

		-- 1.3.6.1.4.1.10106.3.101291.1.1.271
		hsw2000c01v1In1Grp4P1Stat OBJECT-TYPE
			SYNTAX AudioStatus
			MAX-ACCESS read-only
			STATUS current
			DESCRIPTION
				"Audio group 4 pair 1 status"
		::= { hsw2000c01v1Entry 271 }

		-- 1.3.6.1.4.1.10106.3.101291.1.1.272
		hsw2000c01v1In1Grp4P1StatTrapEnable OBJECT-TYPE
			SYNTAX AlarmEnable
			MAX-ACCESS read-write
			STATUS current
			DESCRIPTION
				"Audio group 4 pair 1 status Trap Enable"
		::= { hsw2000c01v1Entry 272 }

		-- 1.3.6.1.4.1.10106.3.101291.1.1.273
		hsw2000c01v1In2Grp1Pres OBJECT-TYPE
			SYNTAX Bit0No1Yes
			MAX-ACCESS read-only
			STATUS current
			DESCRIPTION
				"Audio group 1 packet presence"
		::= { hsw2000c01v1Entry 273 }

		-- 1.3.6.1.4.1.10106.3.101291.1.1.274
		hsw2000c01v1In2Grp1PresTrapEnable OBJECT-TYPE
			SYNTAX AlarmEnable
			MAX-ACCESS read-write
			STATUS current
			DESCRIPTION
				"Audio group 1 packet presence Trap Enable"
		::= { hsw2000c01v1Entry 274 }

		-- 1.3.6.1.4.1.10106.3.101291.1.1.275
		hsw2000c01v1In2Grp2Pres OBJECT-TYPE
			SYNTAX Bit0No1Yes
			MAX-ACCESS read-only
			STATUS current
			DESCRIPTION
				"Audio group 2 packet presence"
		::= { hsw2000c01v1Entry 275 }

		-- 1.3.6.1.4.1.10106.3.101291.1.1.276
		hsw2000c01v1In2Grp2PresTrapEnable OBJECT-TYPE
			SYNTAX AlarmEnable
			MAX-ACCESS read-write
			STATUS current
			DESCRIPTION
				"Audio group 2 packet presence Trap Enable"
		::= { hsw2000c01v1Entry 276 }

		-- 1.3.6.1.4.1.10106.3.101291.1.1.277
		hsw2000c01v1In2Grp3Pres OBJECT-TYPE
			SYNTAX Bit0No1Yes
			MAX-ACCESS read-only
			STATUS current
			DESCRIPTION
				"Audio group 3 packet presence"
		::= { hsw2000c01v1Entry 277 }

		-- 1.3.6.1.4.1.10106.3.101291.1.1.278
		hsw2000c01v1In2Grp3PresTrapEnable OBJECT-TYPE
			SYNTAX AlarmEnable
			MAX-ACCESS read-write
			STATUS current
			DESCRIPTION
				"Audio group 3 packet presence Trap Enable"
		::= { hsw2000c01v1Entry 278 }

		-- 1.3.6.1.4.1.10106.3.101291.1.1.279
		hsw2000c01v1In2Grp4Pres OBJECT-TYPE
			SYNTAX Bit0No1Yes
			MAX-ACCESS read-only
			STATUS current
			DESCRIPTION
				"Audio group 4 packet presence"
		::= { hsw2000c01v1Entry 279 }

		-- 1.3.6.1.4.1.10106.3.101291.1.1.280
		hsw2000c01v1In2Grp4PresTrapEnable OBJECT-TYPE
			SYNTAX AlarmEnable
			MAX-ACCESS read-write
			STATUS current
			DESCRIPTION
				"Audio group 4 packet presence Trap Enable"
		::= { hsw2000c01v1Entry 280 }

		-- 1.3.6.1.4.1.10106.3.101291.1.1.281
		hsw2000c01v1In2Grp1P0Stat OBJECT-TYPE
			SYNTAX AudioStatus
			MAX-ACCESS read-only
			STATUS current
			DESCRIPTION
				"Audio group 1 pair 0 status"
		::= { hsw2000c01v1Entry 281 }

		-- 1.3.6.1.4.1.10106.3.101291.1.1.282
		hsw2000c01v1In2Grp1P0StatTrapEnable OBJECT-TYPE
			SYNTAX AlarmEnable
			MAX-ACCESS read-write
			STATUS current
			DESCRIPTION
				"Audio group 1 pair 0 status Trap Enable"
		::= { hsw2000c01v1Entry 282 }

		-- 1.3.6.1.4.1.10106.3.101291.1.1.283
		hsw2000c01v1In2Grp1P1Stat OBJECT-TYPE
			SYNTAX AudioStatus
			MAX-ACCESS read-only
			STATUS current
			DESCRIPTION
				"Audio group 1 pair 1 status"
		::= { hsw2000c01v1Entry 283 }

		-- 1.3.6.1.4.1.10106.3.101291.1.1.284
		hsw2000c01v1In2Grp1P1StatTrapEnable OBJECT-TYPE
			SYNTAX AlarmEnable
			MAX-ACCESS read-write
			STATUS current
			DESCRIPTION
				"Audio group 1 pair 1 status Trap Enable"
		::= { hsw2000c01v1Entry 284 }

		-- 1.3.6.1.4.1.10106.3.101291.1.1.285
		hsw2000c01v1In2Grp2P0Stat OBJECT-TYPE
			SYNTAX AudioStatus
			MAX-ACCESS read-only
			STATUS current
			DESCRIPTION
				"Audio group 2 pair 0 status"
		::= { hsw2000c01v1Entry 285 }

		-- 1.3.6.1.4.1.10106.3.101291.1.1.286
		hsw2000c01v1In2Grp2P0StatTrapEnable OBJECT-TYPE
			SYNTAX AlarmEnable
			MAX-ACCESS read-write
			STATUS current
			DESCRIPTION
				"Audio group 2 pair 0 status Trap Enable"
		::= { hsw2000c01v1Entry 286 }

		-- 1.3.6.1.4.1.10106.3.101291.1.1.287
		hsw2000c01v1In2Grp2P1Stat OBJECT-TYPE
			SYNTAX AudioStatus
			MAX-ACCESS read-only
			STATUS current
			DESCRIPTION
				"Audio group 2 pair 1status"
		::= { hsw2000c01v1Entry 287 }

		-- 1.3.6.1.4.1.10106.3.101291.1.1.288
		hsw2000c01v1In2Grp2P1StatTrapEnable OBJECT-TYPE
			SYNTAX AlarmEnable
			MAX-ACCESS read-write
			STATUS current
			DESCRIPTION
				"Audio group 2 pair 1status Trap Enable"
		::= { hsw2000c01v1Entry 288 }

		-- 1.3.6.1.4.1.10106.3.101291.1.1.289
		hsw2000c01v1In2Grp3P0Stat OBJECT-TYPE
			SYNTAX AudioStatus
			MAX-ACCESS read-only
			STATUS current
			DESCRIPTION
				"Audio group 3 pair 0 status"
		::= { hsw2000c01v1Entry 289 }

		-- 1.3.6.1.4.1.10106.3.101291.1.1.290
		hsw2000c01v1In2Grp3P0StatTrapEnable OBJECT-TYPE
			SYNTAX AlarmEnable
			MAX-ACCESS read-write
			STATUS current
			DESCRIPTION
				"Audio group 3 pair 0 status Trap Enable"
		::= { hsw2000c01v1Entry 290 }

		-- 1.3.6.1.4.1.10106.3.101291.1.1.291
		hsw2000c01v1In2Grp3P1Stat OBJECT-TYPE
			SYNTAX AudioStatus
			MAX-ACCESS read-only
			STATUS current
			DESCRIPTION
				"Audio group 3 pair 1 status"
		::= { hsw2000c01v1Entry 291 }

		-- 1.3.6.1.4.1.10106.3.101291.1.1.292
		hsw2000c01v1In2Grp3P1StatTrapEnable OBJECT-TYPE
			SYNTAX AlarmEnable
			MAX-ACCESS read-write
			STATUS current
			DESCRIPTION
				"Audio group 3 pair 1 status Trap Enable"
		::= { hsw2000c01v1Entry 292 }

		-- 1.3.6.1.4.1.10106.3.101291.1.1.293
		hsw2000c01v1In2Grp4P0Stat OBJECT-TYPE
			SYNTAX AudioStatus
			MAX-ACCESS read-only
			STATUS current
			DESCRIPTION
				"Audio group 4 pair 0 status"
		::= { hsw2000c01v1Entry 293 }

		-- 1.3.6.1.4.1.10106.3.101291.1.1.294
		hsw2000c01v1In2Grp4P0StatTrapEnable OBJECT-TYPE
			SYNTAX AlarmEnable
			MAX-ACCESS read-write
			STATUS current
			DESCRIPTION
				"Audio group 4 pair 0 status Trap Enable"
		::= { hsw2000c01v1Entry 294 }

		-- 1.3.6.1.4.1.10106.3.101291.1.1.295
		hsw2000c01v1In2Grp4P1Stat OBJECT-TYPE
			SYNTAX AudioStatus
			MAX-ACCESS read-only
			STATUS current
			DESCRIPTION
				"Audio group 4 pair 1 status"
		::= { hsw2000c01v1Entry 295 }

		-- 1.3.6.1.4.1.10106.3.101291.1.1.296
		hsw2000c01v1In2Grp4P1StatTrapEnable OBJECT-TYPE
			SYNTAX AlarmEnable
			MAX-ACCESS read-write
			STATUS current
			DESCRIPTION
				"Audio group 4 pair 1 status Trap Enable"
		::= { hsw2000c01v1Entry 296 }

		-- 1.3.6.1.4.1.10106.3.101291.1.1.297
		hsw2000c01v1In1WssCod OBJECT-TYPE
			SYNTAX Code4Bit
			MAX-ACCESS read-only
			STATUS current
			DESCRIPTION
				"WSS group 1 data  (b3-b0)"
		::= { hsw2000c01v1Entry 297 }

		-- 1.3.6.1.4.1.10106.3.101291.1.1.298
		hsw2000c01v1In1WssCodTrapEnable OBJECT-TYPE
			SYNTAX AlarmEnable
			MAX-ACCESS read-write
			STATUS current
			DESCRIPTION
				"WSS group 1 data  (b3-b0) Trap Enable"
		::= { hsw2000c01v1Entry 298 }

		-- 1.3.6.1.4.1.10106.3.101291.1.1.299
		hsw2000c01v1In1WssStat OBJECT-TYPE
			SYNTAX AfdInfo
			MAX-ACCESS read-only
			STATUS current
			DESCRIPTION
				"WSS information"
		::= { hsw2000c01v1Entry 299 }

		-- 1.3.6.1.4.1.10106.3.101291.1.1.300
		hsw2000c01v1In1WssStatTrapEnable OBJECT-TYPE
			SYNTAX AlarmEnable
			MAX-ACCESS read-write
			STATUS current
			DESCRIPTION
				"WSS information Trap Enable"
		::= { hsw2000c01v1Entry 300 }

		-- 1.3.6.1.4.1.10106.3.101291.1.1.301
		hsw2000c01v1In1ViiAfdCod OBJECT-TYPE
			SYNTAX Code4Bit
			MAX-ACCESS read-only
			STATUS current
			DESCRIPTION
				"VII AFD code (a3-a0)"
		::= { hsw2000c01v1Entry 301 }

		-- 1.3.6.1.4.1.10106.3.101291.1.1.302
		hsw2000c01v1In1ViiAfdCodTrapEnable OBJECT-TYPE
			SYNTAX AlarmEnable
			MAX-ACCESS read-write
			STATUS current
			DESCRIPTION
				"VII AFD code (a3-a0) Trap Enable"
		::= { hsw2000c01v1Entry 302 }

		-- 1.3.6.1.4.1.10106.3.101291.1.1.303
		hsw2000c01v1In1ViiStat OBJECT-TYPE
			SYNTAX AfdInfo
			MAX-ACCESS read-only
			STATUS current
			DESCRIPTION
				"VII information"
		::= { hsw2000c01v1Entry 303 }

		-- 1.3.6.1.4.1.10106.3.101291.1.1.304
		hsw2000c01v1In1ViiStatTrapEnable OBJECT-TYPE
			SYNTAX AlarmEnable
			MAX-ACCESS read-write
			STATUS current
			DESCRIPTION
				"VII information Trap Enable"
		::= { hsw2000c01v1Entry 304 }

		-- 1.3.6.1.4.1.10106.3.101291.1.1.305
		hsw2000c01v1In12016AfdCod OBJECT-TYPE
			SYNTAX Code4Bit
			MAX-ACCESS read-only
			STATUS current
			DESCRIPTION
				"SMPTE 2016 AFD code (a3-a0)"
		::= { hsw2000c01v1Entry 305 }

		-- 1.3.6.1.4.1.10106.3.101291.1.1.306
		hsw2000c01v1In12016AfdCodTrapEnable OBJECT-TYPE
			SYNTAX AlarmEnable
			MAX-ACCESS read-write
			STATUS current
			DESCRIPTION
				"SMPTE 2016 AFD code (a3-a0) Trap Enable"
		::= { hsw2000c01v1Entry 306 }

		-- 1.3.6.1.4.1.10106.3.101291.1.1.307
		hsw2000c01v1In12016Stat OBJECT-TYPE
			SYNTAX AfdInfo
			MAX-ACCESS read-only
			STATUS current
			DESCRIPTION
				"SMPTE 2016 information"
		::= { hsw2000c01v1Entry 307 }

		-- 1.3.6.1.4.1.10106.3.101291.1.1.308
		hsw2000c01v1In12016StatTrapEnable OBJECT-TYPE
			SYNTAX AlarmEnable
			MAX-ACCESS read-write
			STATUS current
			DESCRIPTION
				"SMPTE 2016 information Trap Enable"
		::= { hsw2000c01v1Entry 308 }

		-- 1.3.6.1.4.1.10106.3.101291.1.1.309
		hsw2000c01v1In2WssCod OBJECT-TYPE
			SYNTAX Code4Bit
			MAX-ACCESS read-only
			STATUS current
			DESCRIPTION
				"WSS group 1 data  (b3-b0)"
		::= { hsw2000c01v1Entry 309 }

		-- 1.3.6.1.4.1.10106.3.101291.1.1.310
		hsw2000c01v1In2WssCodTrapEnable OBJECT-TYPE
			SYNTAX AlarmEnable
			MAX-ACCESS read-write
			STATUS current
			DESCRIPTION
				"WSS group 1 data  (b3-b0) Trap Enable"
		::= { hsw2000c01v1Entry 310 }

		-- 1.3.6.1.4.1.10106.3.101291.1.1.311
		hsw2000c01v1In2WssStat OBJECT-TYPE
			SYNTAX AfdInfo
			MAX-ACCESS read-only
			STATUS current
			DESCRIPTION
				"WSS information"
		::= { hsw2000c01v1Entry 311 }

		-- 1.3.6.1.4.1.10106.3.101291.1.1.312
		hsw2000c01v1In2WssStatTrapEnable OBJECT-TYPE
			SYNTAX AlarmEnable
			MAX-ACCESS read-write
			STATUS current
			DESCRIPTION
				"WSS information Trap Enable"
		::= { hsw2000c01v1Entry 312 }

		-- 1.3.6.1.4.1.10106.3.101291.1.1.313
		hsw2000c01v1In2ViiAfdCod OBJECT-TYPE
			SYNTAX Code4Bit
			MAX-ACCESS read-only
			STATUS current
			DESCRIPTION
				"VII AFD code (a3-a0)"
		::= { hsw2000c01v1Entry 313 }

		-- 1.3.6.1.4.1.10106.3.101291.1.1.314
		hsw2000c01v1In2ViiAfdCodTrapEnable OBJECT-TYPE
			SYNTAX AlarmEnable
			MAX-ACCESS read-write
			STATUS current
			DESCRIPTION
				"VII AFD code (a3-a0) Trap Enable"
		::= { hsw2000c01v1Entry 314 }

		-- 1.3.6.1.4.1.10106.3.101291.1.1.315
		hsw2000c01v1In2ViiStat OBJECT-TYPE
			SYNTAX AfdInfo
			MAX-ACCESS read-only
			STATUS current
			DESCRIPTION
				"VII information"
		::= { hsw2000c01v1Entry 315 }

		-- 1.3.6.1.4.1.10106.3.101291.1.1.316
		hsw2000c01v1In2ViiStatTrapEnable OBJECT-TYPE
			SYNTAX AlarmEnable
			MAX-ACCESS read-write
			STATUS current
			DESCRIPTION
				"VII information Trap Enable"
		::= { hsw2000c01v1Entry 316 }

		-- 1.3.6.1.4.1.10106.3.101291.1.1.317
		hsw2000c01v1In22016Cod OBJECT-TYPE
			SYNTAX Code4Bit
			MAX-ACCESS read-only
			STATUS current
			DESCRIPTION
				"SMPTE 2016 AFD code (a3-a0)"
		::= { hsw2000c01v1Entry 317 }

		-- 1.3.6.1.4.1.10106.3.101291.1.1.318
		hsw2000c01v1In22016CodTrapEnable OBJECT-TYPE
			SYNTAX AlarmEnable
			MAX-ACCESS read-write
			STATUS current
			DESCRIPTION
				"SMPTE 2016 AFD code (a3-a0) Trap Enable"
		::= { hsw2000c01v1Entry 318 }

		-- 1.3.6.1.4.1.10106.3.101291.1.1.319
		hsw2000c01v1In22016Stat OBJECT-TYPE
			SYNTAX AfdInfo
			MAX-ACCESS read-only
			STATUS current
			DESCRIPTION
				"SMPTE 2016 information"
		::= { hsw2000c01v1Entry 319 }

		-- 1.3.6.1.4.1.10106.3.101291.1.1.320
		hsw2000c01v1In22016StatTrapEnable OBJECT-TYPE
			SYNTAX AlarmEnable
			MAX-ACCESS read-write
			STATUS current
			DESCRIPTION
				"SMPTE 2016 information Trap Enable"
		::= { hsw2000c01v1Entry 320 }

		-- 1.3.6.1.4.1.10106.3.101291.1.1.321
		hsw2000c01v1In1TxtLinLow OBJECT-TYPE
			SYNTAX Bit0No1Yes
			MAX-ACCESS read-only
			STATUS current
			DESCRIPTION
				"Low level of teletext lines"
		::= { hsw2000c01v1Entry 321 }

		-- 1.3.6.1.4.1.10106.3.101291.1.1.322
		hsw2000c01v1In1TxtLinLowTrapEnable OBJECT-TYPE
			SYNTAX AlarmEnable
			MAX-ACCESS read-write
			STATUS current
			DESCRIPTION
				"Low level of teletext lines Trap Enable"
		::= { hsw2000c01v1Entry 322 }

		-- 1.3.6.1.4.1.10106.3.101291.1.1.323
		hsw2000c01v1In1TxtLin1s OBJECT-TYPE
			SYNTAX Uint11
			MAX-ACCESS read-only
			STATUS current
			DESCRIPTION
				"Number of teletext lines in last second"
		::= { hsw2000c01v1Entry 323 }

		-- 1.3.6.1.4.1.10106.3.101291.1.1.325
		hsw2000c01v1In2TxtLinLow OBJECT-TYPE
			SYNTAX Bit0No1Yes
			MAX-ACCESS read-only
			STATUS current
			DESCRIPTION
				"Low level of teletext lines"
		::= { hsw2000c01v1Entry 325 }

		-- 1.3.6.1.4.1.10106.3.101291.1.1.326
		hsw2000c01v1In2TxtLinLowTrapEnable OBJECT-TYPE
			SYNTAX AlarmEnable
			MAX-ACCESS read-write
			STATUS current
			DESCRIPTION
				"Low level of teletext lines Trap Enable"
		::= { hsw2000c01v1Entry 326 }

		-- 1.3.6.1.4.1.10106.3.101291.1.1.327
		hsw2000c01v1In2TxtLin1s OBJECT-TYPE
			SYNTAX Uint11
			MAX-ACCESS read-only
			STATUS current
			DESCRIPTION
				"Number of teletext lines in last second"
		::= { hsw2000c01v1Entry 327 }

		-- 1.3.6.1.4.1.10106.3.101291.1.1.329
		hsw2000c01v1SerialNo OBJECT-TYPE
			SYNTAX SerialNo
			MAX-ACCESS read-only
			STATUS current
			DESCRIPTION
				"Serial number"
		::= { hsw2000c01v1Entry 329 }

		-- 1.3.6.1.4.1.10106.3.454501
		htg2000c01v1 OBJECT IDENTIFIER ::= { albalaProducts 454501 }

		-- 1.3.6.1.4.1.10106.3.454501.1
		htg2000c01v1Table  OBJECT-TYPE
			SYNTAX SEQUENCE OF Htg2000c01v1Entry
			MAX-ACCESS not-accessible
			STATUS current
			DESCRIPTION
				"Module  HTG2000C01V1 Table"
			::= { htg2000c01v1 1 }

		-- 1.3.6.1.4.1.10106.3.454501.1.1
		htg2000c01v1Entry  OBJECT-TYPE
			SYNTAX Htg2000c01v1Entry
			MAX-ACCESS not-accessible
			STATUS current
			DESCRIPTION
				"Module HTG2000C01V1 Entry"
			INDEX { htg2000c01v1Index }
			::= { htg2000c01v1Table 1 }

			Htg2000c01v1Entry ::=
			SEQUENCE {
				htg2000c01v1Index
				ModuleIndex,
				htg2000c01v1ActivePreset
				Preset16Active,
				htg2000c01v1LoadPreset
				Preset16Load,
				htg2000c01v1SavePreset
				Preset16Save,
				htg2000c01v1ExpRefFormat
				SdiHd3gFmt6,
				htg2000c01v1ExpRefFormatTrapEnable
				AlarmEnable,
				htg2000c01v1RefInput
				RefSel1,
				htg2000c01v1RefInputTrapEnable
				AlarmEnable,
				htg2000c01v1MeasInput
				RefSel1,
				htg2000c01v1OutFormat1
				SdiHd3gFmt6,
				htg2000c01v1OutFormat1TrapEnable
				AlarmEnable,
				htg2000c01v1OutMute1
				Bit0No1Yes,
				htg2000c01v1HDelay1
				DelayPixel4,
				htg2000c01v1VDelay1
				DelayLines2,
				htg2000c01v1TestSignal1
				Uint5,
				htg2000c01v1EnGrp1Aud1
				Bit0No1Yes,
				htg2000c01v1EnGrp2Aud1
				Bit0No1Yes,
				htg2000c01v1EnGrp3Aud1
				Bit0No1Yes,
				htg2000c01v1EnGrp4Aud1
				Bit0No1Yes,
				htg2000c01v1EnOsd1
				Bit0No1Yes,
				htg2000c01v1AudFrP0G01
				AudioFreq1,
				htg2000c01v1AudFrP1G01
				AudioFreq1,
				htg2000c01v1AudFrP0G11
				AudioFreq1,
				htg2000c01v1AudFrP1G11
				AudioFreq1,
				htg2000c01v1AudFrP0G21
				AudioFreq1,
				htg2000c01v1AudFrP1G21
				AudioFreq1,
				htg2000c01v1AudFrP0G31
				AudioFreq1,
				htg2000c01v1AudFrP1G31
				AudioFreq1,
				htg2000c01v1AudDipP0G01
				Bit0Dis1Ena,
				htg2000c01v1AudDipP1G01
				Bit0Dis1Ena,
				htg2000c01v1AudDipP0G11
				Bit0Dis1Ena,
				htg2000c01v1AudDipP1G11
				Bit0Dis1Ena,
				htg2000c01v1AudDipP0G21
				Bit0Dis1Ena,
				htg2000c01v1AudDipP1G21
				Bit0Dis1Ena,
				htg2000c01v1AudDipP0G31
				Bit0Dis1Ena,
				htg2000c01v1AudDipP1G31
				Bit0Dis1Ena,
				htg2000c01v1AudLevP0G01
				AudioLev0,
				htg2000c01v1AudLevP0G11
				AudioLev0,
				htg2000c01v1AudLevP1G01
				AudioLev0,
				htg2000c01v1AudLevP1G11
				AudioLev0,
				htg2000c01v1AudLevP0G21
				AudioLev0,
				htg2000c01v1AudLevP1G21
				AudioLev0,
				htg2000c01v1AudLevP0G31
				AudioLev0,
				htg2000c01v1AudLevP1G31
				AudioLev0,
				htg2000c01v1OutFormat2
				SdiHd3gFmt6,
				htg2000c01v1OutFormat2TrapEnable
				AlarmEnable,
				htg2000c01v1OutMute2
				Bit0No1Yes,
				htg2000c01v1HDelay2
				DelayPixel4,
				htg2000c01v1VDelay2
				DelayLines2,
				htg2000c01v1TestSignal2
				Uint5,
				htg2000c01v1EnGrp1Aud2
				Bit0No1Yes,
				htg2000c01v1EnGrp2Aud2
				Bit0No1Yes,
				htg2000c01v1EnGrp3Aud2
				Bit0No1Yes,
				htg2000c01v1EnGrp4Aud2
				Bit0No1Yes,
				htg2000c01v1EnOsd2
				Bit0No1Yes,
				htg2000c01v1AudFrP0G02
				AudioFreq1,
				htg2000c01v1AudFrP1G02
				AudioFreq1,
				htg2000c01v1AudFrP0G12
				AudioFreq1,
				htg2000c01v1AudFrP1G12
				AudioFreq1,
				htg2000c01v1AudFrP0G22
				AudioFreq1,
				htg2000c01v1AudFrP1G22
				AudioFreq1,
				htg2000c01v1AudFrP0G32
				AudioFreq1,
				htg2000c01v1AudFrP1G32
				AudioFreq1,
				htg2000c01v1AudDipP0G02
				Bit0Dis1Ena,
				htg2000c01v1AudDipP1G02
				Bit0Dis1Ena,
				htg2000c01v1AudDipP0G12
				Bit0Dis1Ena,
				htg2000c01v1AudDipP1G12
				Bit0Dis1Ena,
				htg2000c01v1AudDipP0G22
				Bit0Dis1Ena,
				htg2000c01v1AudDipP1G22
				Bit0Dis1Ena,
				htg2000c01v1AudDipP0G32
				Bit0Dis1Ena,
				htg2000c01v1AudDipP1G32
				Bit0Dis1Ena,
				htg2000c01v1AudLevP0G02
				AudioLev0,
				htg2000c01v1AudLevP0G12
				AudioLev0,
				htg2000c01v1AudLevP1G02
				AudioLev0,
				htg2000c01v1AudLevP1G12
				AudioLev0,
				htg2000c01v1AudLevP0G22
				AudioLev0,
				htg2000c01v1AudLevP1G22
				AudioLev0,
				htg2000c01v1AudLevP0G32
				AudioLev0,
				htg2000c01v1AudLevP1G32
				AudioLev0,
				htg2000c01v1OutFormat3
				SdiHd3gFmt6,
				htg2000c01v1OutFormat3TrapEnable
				AlarmEnable,
				htg2000c01v1HDelay3
				DelayX74Ns,
				htg2000c01v1VDelay3
				DelayLines2,
				htg2000c01v1Sch3
				Sch3,
				htg2000c01v1ArefFailMsk
				BitMask,
				htg2000c01v1DrefFailMsk
				BitMask,
				htg2000c01v1IrefFailMsk
				BitMask,
				htg2000c01v1RefIncFailMsk
				BitMask,
				htg2000c01v1RefLckFailMsk
				BitMask,
				htg2000c01v1ArefFail
				BitFail,
				htg2000c01v1ArefFailTrapEnable
				AlarmEnable,
				htg2000c01v1DrefFail
				BitFail,
				htg2000c01v1DrefFailTrapEnable
				AlarmEnable,
				htg2000c01v1IrefFail
				BitFail,
				htg2000c01v1IrefFailTrapEnable
				AlarmEnable,
				htg2000c01v1RefIncFail
				BitFail,
				htg2000c01v1RefIncFailTrapEnable
				AlarmEnable,
				htg2000c01v1RefLockFail
				BitFail,
				htg2000c01v1RefLockFailTrapEnable
				AlarmEnable,
				htg2000c01v1DrefCrcFail
				BitFail,
				htg2000c01v1DrefCrcFailTrapEnable
				AlarmEnable,
				htg2000c01v1ArefFormat
				SdiHd3gFmt3,
				htg2000c01v1ArefFormatTrapEnable
				AlarmEnable,
				htg2000c01v1DrefFormat
				SdiHd3gFmt3,
				htg2000c01v1DrefFormatTrapEnable
				AlarmEnable,
				htg2000c01v1MeasDelay
				DelayX74Ns,
				htg2000c01v1MeasFreq
				FrqDrft3,
				htg2000c01v1SerialNo
				SerialNo
			 }

		-- 1.3.6.1.4.1.10106.3.101291.1.1.1
		htg2000c01v1Index OBJECT-TYPE
			SYNTAX ModuleIndex
			MAX-ACCESS read-only
			STATUS current
			DESCRIPTION
				"Index of HTG2000C01V1 Table"
		::= { htg2000c01v1Entry 1 }

		-- 1.3.6.1.4.1.10106.3.101291.1.1.3
		htg2000c01v1ActivePreset OBJECT-TYPE
			SYNTAX Preset16Active
			MAX-ACCESS read-only
			STATUS current
			DESCRIPTION
				"Shows the active preset"
		::= { htg2000c01v1Entry 3 }

		-- 1.3.6.1.4.1.10106.3.101291.1.1.5
		htg2000c01v1LoadPreset OBJECT-TYPE
			SYNTAX Preset16Load
			MAX-ACCESS read-write
			STATUS current
			DESCRIPTION
				"Allows loading a preset"
		::= { htg2000c01v1Entry 5 }

		-- 1.3.6.1.4.1.10106.3.101291.1.1.7
		htg2000c01v1SavePreset OBJECT-TYPE
			SYNTAX Preset16Save
			MAX-ACCESS read-write
			STATUS current
			DESCRIPTION
				"Allows saving a preset"
		::= { htg2000c01v1Entry 7 }

		-- 1.3.6.1.4.1.10106.3.101291.1.1.9
		htg2000c01v1ExpRefFormat OBJECT-TYPE
			SYNTAX SdiHd3gFmt6
			MAX-ACCESS read-write
			STATUS current
			DESCRIPTION
				"Allows selecting the expected format of the reference"
		::= { htg2000c01v1Entry 9 }

		-- 1.3.6.1.4.1.10106.3.101291.1.1.10
		htg2000c01v1ExpRefFormatTrapEnable OBJECT-TYPE
			SYNTAX AlarmEnable
			MAX-ACCESS read-write
			STATUS current
			DESCRIPTION
				"Allows selecting the expected format of the reference Trap Enable"
		::= { htg2000c01v1Entry 10 }

		-- 1.3.6.1.4.1.10106.3.101291.1.1.11
		htg2000c01v1RefInput OBJECT-TYPE
			SYNTAX RefSel1
			MAX-ACCESS read-write
			STATUS current
			DESCRIPTION
				"Allows selecting the reference input"
		::= { htg2000c01v1Entry 11 }

		-- 1.3.6.1.4.1.10106.3.101291.1.1.12
		htg2000c01v1RefInputTrapEnable OBJECT-TYPE
			SYNTAX AlarmEnable
			MAX-ACCESS read-write
			STATUS current
			DESCRIPTION
				"Allows selecting the reference input Trap Enable"
		::= { htg2000c01v1Entry 12 }

		-- 1.3.6.1.4.1.10106.3.101291.1.1.13
		htg2000c01v1MeasInput OBJECT-TYPE
			SYNTAX RefSel1
			MAX-ACCESS read-write
			STATUS current
			DESCRIPTION
				"Allows selecting the input used for delay mesaurement"
		::= { htg2000c01v1Entry 13 }

		-- 1.3.6.1.4.1.10106.3.101291.1.1.15
		htg2000c01v1OutFormat1 OBJECT-TYPE
			SYNTAX SdiHd3gFmt6
			MAX-ACCESS read-write
			STATUS current
			DESCRIPTION
				"Allows selecting the output format"
		::= { htg2000c01v1Entry 15 }

		-- 1.3.6.1.4.1.10106.3.101291.1.1.16
		htg2000c01v1OutFormat1TrapEnable OBJECT-TYPE
			SYNTAX AlarmEnable
			MAX-ACCESS read-write
			STATUS current
			DESCRIPTION
				"Allows selecting the output format Trap Enable"
		::= { htg2000c01v1Entry 16 }

		-- 1.3.6.1.4.1.10106.3.101291.1.1.17
		htg2000c01v1OutMute1 OBJECT-TYPE
			SYNTAX Bit0No1Yes
			MAX-ACCESS read-write
			STATUS current
			DESCRIPTION
				"Allows disabling the output"
		::= { htg2000c01v1Entry 17 }

		-- 1.3.6.1.4.1.10106.3.101291.1.1.19
		htg2000c01v1HDelay1 OBJECT-TYPE
			SYNTAX DelayPixel4
			MAX-ACCESS read-write
			STATUS current
			DESCRIPTION
				"Allows adjusting the video horizontal delay of main output"
		::= { htg2000c01v1Entry 19 }

		-- 1.3.6.1.4.1.10106.3.101291.1.1.21
		htg2000c01v1VDelay1 OBJECT-TYPE
			SYNTAX DelayLines2
			MAX-ACCESS read-write
			STATUS current
			DESCRIPTION
				"Allows adjusting the video vertical delay of main output"
		::= { htg2000c01v1Entry 21 }

		-- 1.3.6.1.4.1.10106.3.101291.1.1.23
		htg2000c01v1TestSignal1 OBJECT-TYPE
			SYNTAX Uint5
			MAX-ACCESS read-write
			STATUS current
			DESCRIPTION
				"Allows selecting the generated video signal pattern"
		::= { htg2000c01v1Entry 23 }

		-- 1.3.6.1.4.1.10106.3.101291.1.1.25
		htg2000c01v1EnGrp1Aud1 OBJECT-TYPE
			SYNTAX Bit0No1Yes
			MAX-ACCESS read-write
			STATUS current
			DESCRIPTION
				"Allows inserting group 1 audio packets"
		::= { htg2000c01v1Entry 25 }

		-- 1.3.6.1.4.1.10106.3.101291.1.1.27
		htg2000c01v1EnGrp2Aud1 OBJECT-TYPE
			SYNTAX Bit0No1Yes
			MAX-ACCESS read-write
			STATUS current
			DESCRIPTION
				"Allows inserting group 2 audio packets"
		::= { htg2000c01v1Entry 27 }

		-- 1.3.6.1.4.1.10106.3.101291.1.1.29
		htg2000c01v1EnGrp3Aud1 OBJECT-TYPE
			SYNTAX Bit0No1Yes
			MAX-ACCESS read-write
			STATUS current
			DESCRIPTION
				"Allows inserting group 3 audio packets"
		::= { htg2000c01v1Entry 29 }

		-- 1.3.6.1.4.1.10106.3.101291.1.1.31
		htg2000c01v1EnGrp4Aud1 OBJECT-TYPE
			SYNTAX Bit0No1Yes
			MAX-ACCESS read-write
			STATUS current
			DESCRIPTION
				"Allows inserting group 4 audio packets"
		::= { htg2000c01v1Entry 31 }

		-- 1.3.6.1.4.1.10106.3.101291.1.1.33
		htg2000c01v1EnOsd1 OBJECT-TYPE
			SYNTAX Bit0No1Yes
			MAX-ACCESS read-write
			STATUS current
			DESCRIPTION
				"Allows inserting on sreen display caption"
		::= { htg2000c01v1Entry 33 }

		-- 1.3.6.1.4.1.10106.3.101291.1.1.35
		htg2000c01v1AudFrP0G01 OBJECT-TYPE
			SYNTAX AudioFreq1
			MAX-ACCESS read-write
			STATUS current
			DESCRIPTION
				"Allows selecting the audio signal in pair 0 group 1"
		::= { htg2000c01v1Entry 35 }

		-- 1.3.6.1.4.1.10106.3.101291.1.1.37
		htg2000c01v1AudFrP1G01 OBJECT-TYPE
			SYNTAX AudioFreq1
			MAX-ACCESS read-write
			STATUS current
			DESCRIPTION
				"Allows selecting the audio signal in pair 1 group 1"
		::= { htg2000c01v1Entry 37 }

		-- 1.3.6.1.4.1.10106.3.101291.1.1.39
		htg2000c01v1AudFrP0G11 OBJECT-TYPE
			SYNTAX AudioFreq1
			MAX-ACCESS read-write
			STATUS current
			DESCRIPTION
				"Allows selecting the audio signal in pair 0 group 2"
		::= { htg2000c01v1Entry 39 }

		-- 1.3.6.1.4.1.10106.3.101291.1.1.41
		htg2000c01v1AudFrP1G11 OBJECT-TYPE
			SYNTAX AudioFreq1
			MAX-ACCESS read-write
			STATUS current
			DESCRIPTION
				"Allows selecting the audio signal in pair 1 group 2"
		::= { htg2000c01v1Entry 41 }

		-- 1.3.6.1.4.1.10106.3.101291.1.1.43
		htg2000c01v1AudFrP0G21 OBJECT-TYPE
			SYNTAX AudioFreq1
			MAX-ACCESS read-write
			STATUS current
			DESCRIPTION
				"Allows selecting the audio signal in pair 0 group 3"
		::= { htg2000c01v1Entry 43 }

		-- 1.3.6.1.4.1.10106.3.101291.1.1.45
		htg2000c01v1AudFrP1G21 OBJECT-TYPE
			SYNTAX AudioFreq1
			MAX-ACCESS read-write
			STATUS current
			DESCRIPTION
				"Allows selecting the audio signal in pair 1 group 3"
		::= { htg2000c01v1Entry 45 }

		-- 1.3.6.1.4.1.10106.3.101291.1.1.47
		htg2000c01v1AudFrP0G31 OBJECT-TYPE
			SYNTAX AudioFreq1
			MAX-ACCESS read-write
			STATUS current
			DESCRIPTION
				"Allows selecting the audio signal in pair 0 group 4"
		::= { htg2000c01v1Entry 47 }

		-- 1.3.6.1.4.1.10106.3.101291.1.1.49
		htg2000c01v1AudFrP1G31 OBJECT-TYPE
			SYNTAX AudioFreq1
			MAX-ACCESS read-write
			STATUS current
			DESCRIPTION
				"Allows selecting the audio signal in pair 1 group 4"
		::= { htg2000c01v1Entry 49 }

		-- 1.3.6.1.4.1.10106.3.101291.1.1.51
		htg2000c01v1AudDipP0G01 OBJECT-TYPE
			SYNTAX Bit0Dis1Ena
			MAX-ACCESS read-write
			STATUS current
			DESCRIPTION
				"Allows enabling the insertion of silences for channel identification in pair 0 group 1"
		::= { htg2000c01v1Entry 51 }

		-- 1.3.6.1.4.1.10106.3.101291.1.1.53
		htg2000c01v1AudDipP1G01 OBJECT-TYPE
			SYNTAX Bit0Dis1Ena
			MAX-ACCESS read-write
			STATUS current
			DESCRIPTION
				"Allows enabling the insertion of silences for channel identification in pair 1 group 1"
		::= { htg2000c01v1Entry 53 }

		-- 1.3.6.1.4.1.10106.3.101291.1.1.55
		htg2000c01v1AudDipP0G11 OBJECT-TYPE
			SYNTAX Bit0Dis1Ena
			MAX-ACCESS read-write
			STATUS current
			DESCRIPTION
				"Allows enabling the insertion of silences for channel identification in pair 0 group 2"
		::= { htg2000c01v1Entry 55 }

		-- 1.3.6.1.4.1.10106.3.101291.1.1.57
		htg2000c01v1AudDipP1G11 OBJECT-TYPE
			SYNTAX Bit0Dis1Ena
			MAX-ACCESS read-write
			STATUS current
			DESCRIPTION
				"Allows enabling the insertion of silences for channel identification in pair 1 group 2"
		::= { htg2000c01v1Entry 57 }

		-- 1.3.6.1.4.1.10106.3.101291.1.1.59
		htg2000c01v1AudDipP0G21 OBJECT-TYPE
			SYNTAX Bit0Dis1Ena
			MAX-ACCESS read-write
			STATUS current
			DESCRIPTION
				"Allows enabling the insertion of silences for channel identification in pair 0 group 3"
		::= { htg2000c01v1Entry 59 }

		-- 1.3.6.1.4.1.10106.3.101291.1.1.61
		htg2000c01v1AudDipP1G21 OBJECT-TYPE
			SYNTAX Bit0Dis1Ena
			MAX-ACCESS read-write
			STATUS current
			DESCRIPTION
				"Allows enabling the insertion of silences for channel identification in pair 1 group 3"
		::= { htg2000c01v1Entry 61 }

		-- 1.3.6.1.4.1.10106.3.101291.1.1.63
		htg2000c01v1AudDipP0G31 OBJECT-TYPE
			SYNTAX Bit0Dis1Ena
			MAX-ACCESS read-write
			STATUS current
			DESCRIPTION
				"Allows enabling the insertion of silences for channel identification in pair 0 group 4"
		::= { htg2000c01v1Entry 63 }

		-- 1.3.6.1.4.1.10106.3.101291.1.1.65
		htg2000c01v1AudDipP1G31 OBJECT-TYPE
			SYNTAX Bit0Dis1Ena
			MAX-ACCESS read-write
			STATUS current
			DESCRIPTION
				"Allows enabling the insertion of silences for channel identification in pair 1 group 4"
		::= { htg2000c01v1Entry 65 }

		-- 1.3.6.1.4.1.10106.3.101291.1.1.67
		htg2000c01v1AudLevP0G01 OBJECT-TYPE
			SYNTAX AudioLev0
			MAX-ACCESS read-write
			STATUS current
			DESCRIPTION
				"Allows selecting the audio level in pair 0 group 1"
		::= { htg2000c01v1Entry 67 }

		-- 1.3.6.1.4.1.10106.3.101291.1.1.69
		htg2000c01v1AudLevP0G11 OBJECT-TYPE
			SYNTAX AudioLev0
			MAX-ACCESS read-write
			STATUS current
			DESCRIPTION
				"Allows selecting the audio level in pair 1 group 1"
		::= { htg2000c01v1Entry 69 }

		-- 1.3.6.1.4.1.10106.3.101291.1.1.71
		htg2000c01v1AudLevP1G01 OBJECT-TYPE
			SYNTAX AudioLev0
			MAX-ACCESS read-write
			STATUS current
			DESCRIPTION
				"Allows selecting the audio level in pair 0 group 2"
		::= { htg2000c01v1Entry 71 }

		-- 1.3.6.1.4.1.10106.3.101291.1.1.73
		htg2000c01v1AudLevP1G11 OBJECT-TYPE
			SYNTAX AudioLev0
			MAX-ACCESS read-write
			STATUS current
			DESCRIPTION
				"Allows selecting the audio level in pair 1 group 2"
		::= { htg2000c01v1Entry 73 }

		-- 1.3.6.1.4.1.10106.3.101291.1.1.75
		htg2000c01v1AudLevP0G21 OBJECT-TYPE
			SYNTAX AudioLev0
			MAX-ACCESS read-write
			STATUS current
			DESCRIPTION
				"Allows selecting the audio level in pair 0 group 3"
		::= { htg2000c01v1Entry 75 }

		-- 1.3.6.1.4.1.10106.3.101291.1.1.77
		htg2000c01v1AudLevP1G21 OBJECT-TYPE
			SYNTAX AudioLev0
			MAX-ACCESS read-write
			STATUS current
			DESCRIPTION
				"Allows selecting the audio level in pair 1 group 3"
		::= { htg2000c01v1Entry 77 }

		-- 1.3.6.1.4.1.10106.3.101291.1.1.79
		htg2000c01v1AudLevP0G31 OBJECT-TYPE
			SYNTAX AudioLev0
			MAX-ACCESS read-write
			STATUS current
			DESCRIPTION
				"Allows selecting the audio level in pair 0 group 4"
		::= { htg2000c01v1Entry 79 }

		-- 1.3.6.1.4.1.10106.3.101291.1.1.81
		htg2000c01v1AudLevP1G31 OBJECT-TYPE
			SYNTAX AudioLev0
			MAX-ACCESS read-write
			STATUS current
			DESCRIPTION
				"Allows selecting the audio level in pair 1 group 4"
		::= { htg2000c01v1Entry 81 }

		-- 1.3.6.1.4.1.10106.3.101291.1.1.83
		htg2000c01v1OutFormat2 OBJECT-TYPE
			SYNTAX SdiHd3gFmt6
			MAX-ACCESS read-write
			STATUS current
			DESCRIPTION
				"Allows selecting the output format"
		::= { htg2000c01v1Entry 83 }

		-- 1.3.6.1.4.1.10106.3.101291.1.1.84
		htg2000c01v1OutFormat2TrapEnable OBJECT-TYPE
			SYNTAX AlarmEnable
			MAX-ACCESS read-write
			STATUS current
			DESCRIPTION
				"Allows selecting the output format Trap Enable"
		::= { htg2000c01v1Entry 84 }

		-- 1.3.6.1.4.1.10106.3.101291.1.1.85
		htg2000c01v1OutMute2 OBJECT-TYPE
			SYNTAX Bit0No1Yes
			MAX-ACCESS read-write
			STATUS current
			DESCRIPTION
				"Allows disabling the output"
		::= { htg2000c01v1Entry 85 }

		-- 1.3.6.1.4.1.10106.3.101291.1.1.87
		htg2000c01v1HDelay2 OBJECT-TYPE
			SYNTAX DelayPixel4
			MAX-ACCESS read-write
			STATUS current
			DESCRIPTION
				"Allows adjusting the video horizontal delay of main output"
		::= { htg2000c01v1Entry 87 }

		-- 1.3.6.1.4.1.10106.3.101291.1.1.89
		htg2000c01v1VDelay2 OBJECT-TYPE
			SYNTAX DelayLines2
			MAX-ACCESS read-write
			STATUS current
			DESCRIPTION
				"Allows adjusting the video vertical delay of main output"
		::= { htg2000c01v1Entry 89 }

		-- 1.3.6.1.4.1.10106.3.101291.1.1.91
		htg2000c01v1TestSignal2 OBJECT-TYPE
			SYNTAX Uint5
			MAX-ACCESS read-write
			STATUS current
			DESCRIPTION
				"Allows selecting the generated video signal pattern"
		::= { htg2000c01v1Entry 91 }

		-- 1.3.6.1.4.1.10106.3.101291.1.1.93
		htg2000c01v1EnGrp1Aud2 OBJECT-TYPE
			SYNTAX Bit0No1Yes
			MAX-ACCESS read-write
			STATUS current
			DESCRIPTION
				"Allows inserting group 1 audio packets"
		::= { htg2000c01v1Entry 93 }

		-- 1.3.6.1.4.1.10106.3.101291.1.1.95
		htg2000c01v1EnGrp2Aud2 OBJECT-TYPE
			SYNTAX Bit0No1Yes
			MAX-ACCESS read-write
			STATUS current
			DESCRIPTION
				"Allows inserting group 2 audio packets"
		::= { htg2000c01v1Entry 95 }

		-- 1.3.6.1.4.1.10106.3.101291.1.1.97
		htg2000c01v1EnGrp3Aud2 OBJECT-TYPE
			SYNTAX Bit0No1Yes
			MAX-ACCESS read-write
			STATUS current
			DESCRIPTION
				"Allows inserting group 3 audio packets"
		::= { htg2000c01v1Entry 97 }

		-- 1.3.6.1.4.1.10106.3.101291.1.1.99
		htg2000c01v1EnGrp4Aud2 OBJECT-TYPE
			SYNTAX Bit0No1Yes
			MAX-ACCESS read-write
			STATUS current
			DESCRIPTION
				"Allows inserting group 4 audio packets"
		::= { htg2000c01v1Entry 99 }

		-- 1.3.6.1.4.1.10106.3.101291.1.1.101
		htg2000c01v1EnOsd2 OBJECT-TYPE
			SYNTAX Bit0No1Yes
			MAX-ACCESS read-write
			STATUS current
			DESCRIPTION
				"Allows inserting on sreen display caption"
		::= { htg2000c01v1Entry 101 }

		-- 1.3.6.1.4.1.10106.3.101291.1.1.103
		htg2000c01v1AudFrP0G02 OBJECT-TYPE
			SYNTAX AudioFreq1
			MAX-ACCESS read-write
			STATUS current
			DESCRIPTION
				"Allows selecting the audio signal in pair 0 group 1"
		::= { htg2000c01v1Entry 103 }

		-- 1.3.6.1.4.1.10106.3.101291.1.1.105
		htg2000c01v1AudFrP1G02 OBJECT-TYPE
			SYNTAX AudioFreq1
			MAX-ACCESS read-write
			STATUS current
			DESCRIPTION
				"Allows selecting the audio signal in pair 1 group 1"
		::= { htg2000c01v1Entry 105 }

		-- 1.3.6.1.4.1.10106.3.101291.1.1.107
		htg2000c01v1AudFrP0G12 OBJECT-TYPE
			SYNTAX AudioFreq1
			MAX-ACCESS read-write
			STATUS current
			DESCRIPTION
				"Allows selecting the audio signal in pair 0 group 2"
		::= { htg2000c01v1Entry 107 }

		-- 1.3.6.1.4.1.10106.3.101291.1.1.109
		htg2000c01v1AudFrP1G12 OBJECT-TYPE
			SYNTAX AudioFreq1
			MAX-ACCESS read-write
			STATUS current
			DESCRIPTION
				"Allows selecting the audio signal in pair 1 group 2"
		::= { htg2000c01v1Entry 109 }

		-- 1.3.6.1.4.1.10106.3.101291.1.1.111
		htg2000c01v1AudFrP0G22 OBJECT-TYPE
			SYNTAX AudioFreq1
			MAX-ACCESS read-write
			STATUS current
			DESCRIPTION
				"Allows selecting the audio signal in pair 0 group 3"
		::= { htg2000c01v1Entry 111 }

		-- 1.3.6.1.4.1.10106.3.101291.1.1.113
		htg2000c01v1AudFrP1G22 OBJECT-TYPE
			SYNTAX AudioFreq1
			MAX-ACCESS read-write
			STATUS current
			DESCRIPTION
				"Allows selecting the audio signal in pair 1 group 3"
		::= { htg2000c01v1Entry 113 }

		-- 1.3.6.1.4.1.10106.3.101291.1.1.115
		htg2000c01v1AudFrP0G32 OBJECT-TYPE
			SYNTAX AudioFreq1
			MAX-ACCESS read-write
			STATUS current
			DESCRIPTION
				"Allows selecting the audio signal in pair 0 group 4"
		::= { htg2000c01v1Entry 115 }

		-- 1.3.6.1.4.1.10106.3.101291.1.1.117
		htg2000c01v1AudFrP1G32 OBJECT-TYPE
			SYNTAX AudioFreq1
			MAX-ACCESS read-write
			STATUS current
			DESCRIPTION
				"Allows selecting the audio signal in pair 1 group 4"
		::= { htg2000c01v1Entry 117 }

		-- 1.3.6.1.4.1.10106.3.101291.1.1.119
		htg2000c01v1AudDipP0G02 OBJECT-TYPE
			SYNTAX Bit0Dis1Ena
			MAX-ACCESS read-write
			STATUS current
			DESCRIPTION
				"Allows enabling the insertion of silences for channel identification in pair 0 group 1"
		::= { htg2000c01v1Entry 119 }

		-- 1.3.6.1.4.1.10106.3.101291.1.1.121
		htg2000c01v1AudDipP1G02 OBJECT-TYPE
			SYNTAX Bit0Dis1Ena
			MAX-ACCESS read-write
			STATUS current
			DESCRIPTION
				"Allows enabling the insertion of silences for channel identification in pair 1 group 1"
		::= { htg2000c01v1Entry 121 }

		-- 1.3.6.1.4.1.10106.3.101291.1.1.123
		htg2000c01v1AudDipP0G12 OBJECT-TYPE
			SYNTAX Bit0Dis1Ena
			MAX-ACCESS read-write
			STATUS current
			DESCRIPTION
				"Allows enabling the insertion of silences for channel identification in pair 0 group 2"
		::= { htg2000c01v1Entry 123 }

		-- 1.3.6.1.4.1.10106.3.101291.1.1.125
		htg2000c01v1AudDipP1G12 OBJECT-TYPE
			SYNTAX Bit0Dis1Ena
			MAX-ACCESS read-write
			STATUS current
			DESCRIPTION
				"Allows enabling the insertion of silences for channel identification in pair 1 group 2"
		::= { htg2000c01v1Entry 125 }

		-- 1.3.6.1.4.1.10106.3.101291.1.1.127
		htg2000c01v1AudDipP0G22 OBJECT-TYPE
			SYNTAX Bit0Dis1Ena
			MAX-ACCESS read-write
			STATUS current
			DESCRIPTION
				"Allows enabling the insertion of silences for channel identification in pair 0 group 3"
		::= { htg2000c01v1Entry 127 }

		-- 1.3.6.1.4.1.10106.3.101291.1.1.129
		htg2000c01v1AudDipP1G22 OBJECT-TYPE
			SYNTAX Bit0Dis1Ena
			MAX-ACCESS read-write
			STATUS current
			DESCRIPTION
				"Allows enabling the insertion of silences for channel identification in pair 1 group 3"
		::= { htg2000c01v1Entry 129 }

		-- 1.3.6.1.4.1.10106.3.101291.1.1.131
		htg2000c01v1AudDipP0G32 OBJECT-TYPE
			SYNTAX Bit0Dis1Ena
			MAX-ACCESS read-write
			STATUS current
			DESCRIPTION
				"Allows enabling the insertion of silences for channel identification in pair 0 group 4"
		::= { htg2000c01v1Entry 131 }

		-- 1.3.6.1.4.1.10106.3.101291.1.1.133
		htg2000c01v1AudDipP1G32 OBJECT-TYPE
			SYNTAX Bit0Dis1Ena
			MAX-ACCESS read-write
			STATUS current
			DESCRIPTION
				"Allows enabling the insertion of silences for channel identification in pair 1 group 4"
		::= { htg2000c01v1Entry 133 }

		-- 1.3.6.1.4.1.10106.3.101291.1.1.135
		htg2000c01v1AudLevP0G02 OBJECT-TYPE
			SYNTAX AudioLev0
			MAX-ACCESS read-write
			STATUS current
			DESCRIPTION
				"Allows selecting the audio level in pair 0 group 1"
		::= { htg2000c01v1Entry 135 }

		-- 1.3.6.1.4.1.10106.3.101291.1.1.137
		htg2000c01v1AudLevP0G12 OBJECT-TYPE
			SYNTAX AudioLev0
			MAX-ACCESS read-write
			STATUS current
			DESCRIPTION
				"Allows selecting the audio level in pair 1 group 1"
		::= { htg2000c01v1Entry 137 }

		-- 1.3.6.1.4.1.10106.3.101291.1.1.139
		htg2000c01v1AudLevP1G02 OBJECT-TYPE
			SYNTAX AudioLev0
			MAX-ACCESS read-write
			STATUS current
			DESCRIPTION
				"Allows selecting the audio level in pair 0 group 2"
		::= { htg2000c01v1Entry 139 }

		-- 1.3.6.1.4.1.10106.3.101291.1.1.141
		htg2000c01v1AudLevP1G12 OBJECT-TYPE
			SYNTAX AudioLev0
			MAX-ACCESS read-write
			STATUS current
			DESCRIPTION
				"Allows selecting the audio level in pair 1 group 2"
		::= { htg2000c01v1Entry 141 }

		-- 1.3.6.1.4.1.10106.3.101291.1.1.143
		htg2000c01v1AudLevP0G22 OBJECT-TYPE
			SYNTAX AudioLev0
			MAX-ACCESS read-write
			STATUS current
			DESCRIPTION
				"Allows selecting the audio level in pair 0 group 3"
		::= { htg2000c01v1Entry 143 }

		-- 1.3.6.1.4.1.10106.3.101291.1.1.145
		htg2000c01v1AudLevP1G22 OBJECT-TYPE
			SYNTAX AudioLev0
			MAX-ACCESS read-write
			STATUS current
			DESCRIPTION
				"Allows selecting the audio level in pair 1 group 3"
		::= { htg2000c01v1Entry 145 }

		-- 1.3.6.1.4.1.10106.3.101291.1.1.147
		htg2000c01v1AudLevP0G32 OBJECT-TYPE
			SYNTAX AudioLev0
			MAX-ACCESS read-write
			STATUS current
			DESCRIPTION
				"Allows selecting the audio level in pair 0 group 4"
		::= { htg2000c01v1Entry 147 }

		-- 1.3.6.1.4.1.10106.3.101291.1.1.149
		htg2000c01v1AudLevP1G32 OBJECT-TYPE
			SYNTAX AudioLev0
			MAX-ACCESS read-write
			STATUS current
			DESCRIPTION
				"Allows selecting the audio level in pair 1 group 4"
		::= { htg2000c01v1Entry 149 }

		-- 1.3.6.1.4.1.10106.3.101291.1.1.151
		htg2000c01v1OutFormat3 OBJECT-TYPE
			SYNTAX SdiHd3gFmt6
			MAX-ACCESS read-write
			STATUS current
			DESCRIPTION
				"Allows selecting the output format"
		::= { htg2000c01v1Entry 151 }

		-- 1.3.6.1.4.1.10106.3.101291.1.1.152
		htg2000c01v1OutFormat3TrapEnable OBJECT-TYPE
			SYNTAX AlarmEnable
			MAX-ACCESS read-write
			STATUS current
			DESCRIPTION
				"Allows selecting the output format Trap Enable"
		::= { htg2000c01v1Entry 152 }

		-- 1.3.6.1.4.1.10106.3.101291.1.1.153
		htg2000c01v1HDelay3 OBJECT-TYPE
			SYNTAX DelayX74Ns
			MAX-ACCESS read-write
			STATUS current
			DESCRIPTION
				"Allows adjusting the video horizontal delay of main output"
		::= { htg2000c01v1Entry 153 }

		-- 1.3.6.1.4.1.10106.3.101291.1.1.155
		htg2000c01v1VDelay3 OBJECT-TYPE
			SYNTAX DelayLines2
			MAX-ACCESS read-write
			STATUS current
			DESCRIPTION
				"Allows adjusting the video vertical delay of main output"
		::= { htg2000c01v1Entry 155 }

		-- 1.3.6.1.4.1.10106.3.101291.1.1.157
		htg2000c01v1Sch3 OBJECT-TYPE
			SYNTAX Sch3
			MAX-ACCESS read-write
			STATUS current
			DESCRIPTION
				"Allows adjusting the SCH"
		::= { htg2000c01v1Entry 157 }

		-- 1.3.6.1.4.1.10106.3.101291.1.1.159
		htg2000c01v1ArefFailMsk OBJECT-TYPE
			SYNTAX BitMask
			MAX-ACCESS read-write
			STATUS current
			DESCRIPTION
				"Allows masking the analog reference absence fail"
		::= { htg2000c01v1Entry 159 }

		-- 1.3.6.1.4.1.10106.3.101291.1.1.161
		htg2000c01v1DrefFailMsk OBJECT-TYPE
			SYNTAX BitMask
			MAX-ACCESS read-write
			STATUS current
			DESCRIPTION
				"Allows masking the digital reference absence fail"
		::= { htg2000c01v1Entry 161 }

		-- 1.3.6.1.4.1.10106.3.101291.1.1.163
		htg2000c01v1IrefFailMsk OBJECT-TYPE
			SYNTAX BitMask
			MAX-ACCESS read-write
			STATUS current
			DESCRIPTION
				"Allows masking the internal reference absence fail"
		::= { htg2000c01v1Entry 163 }

		-- 1.3.6.1.4.1.10106.3.101291.1.1.165
		htg2000c01v1RefIncFailMsk OBJECT-TYPE
			SYNTAX BitMask
			MAX-ACCESS read-write
			STATUS current
			DESCRIPTION
				"Allows masking the different reference format fail"
		::= { htg2000c01v1Entry 165 }

		-- 1.3.6.1.4.1.10106.3.101291.1.1.167
		htg2000c01v1RefLckFailMsk OBJECT-TYPE
			SYNTAX BitMask
			MAX-ACCESS read-write
			STATUS current
			DESCRIPTION
				"Allows masking the reference lock fail"
		::= { htg2000c01v1Entry 167 }

		-- 1.3.6.1.4.1.10106.3.101291.1.1.169
		htg2000c01v1ArefFail OBJECT-TYPE
			SYNTAX BitFail
			MAX-ACCESS read-only
			STATUS current
			DESCRIPTION
				"Indicates the absence of analog reference"
		::= { htg2000c01v1Entry 169 }

		-- 1.3.6.1.4.1.10106.3.101291.1.1.170
		htg2000c01v1ArefFailTrapEnable OBJECT-TYPE
			SYNTAX AlarmEnable
			MAX-ACCESS read-write
			STATUS current
			DESCRIPTION
				"Indicates the absence of analog reference Trap Enable"
		::= { htg2000c01v1Entry 170 }

		-- 1.3.6.1.4.1.10106.3.101291.1.1.171
		htg2000c01v1DrefFail OBJECT-TYPE
			SYNTAX BitFail
			MAX-ACCESS read-only
			STATUS current
			DESCRIPTION
				"Indicates the absence of digital reference"
		::= { htg2000c01v1Entry 171 }

		-- 1.3.6.1.4.1.10106.3.101291.1.1.172
		htg2000c01v1DrefFailTrapEnable OBJECT-TYPE
			SYNTAX AlarmEnable
			MAX-ACCESS read-write
			STATUS current
			DESCRIPTION
				"Indicates the absence of digital reference Trap Enable"
		::= { htg2000c01v1Entry 172 }

		-- 1.3.6.1.4.1.10106.3.101291.1.1.173
		htg2000c01v1IrefFail OBJECT-TYPE
			SYNTAX BitFail
			MAX-ACCESS read-only
			STATUS current
			DESCRIPTION
				"Indicates the absence of internal reference"
		::= { htg2000c01v1Entry 173 }

		-- 1.3.6.1.4.1.10106.3.101291.1.1.174
		htg2000c01v1IrefFailTrapEnable OBJECT-TYPE
			SYNTAX AlarmEnable
			MAX-ACCESS read-write
			STATUS current
			DESCRIPTION
				"Indicates the absence of internal reference Trap Enable"
		::= { htg2000c01v1Entry 174 }

		-- 1.3.6.1.4.1.10106.3.101291.1.1.175
		htg2000c01v1RefIncFail OBJECT-TYPE
			SYNTAX BitFail
			MAX-ACCESS read-only
			STATUS current
			DESCRIPTION
				"Indicates that the format of the received reference is different from expected"
		::= { htg2000c01v1Entry 175 }

		-- 1.3.6.1.4.1.10106.3.101291.1.1.176
		htg2000c01v1RefIncFailTrapEnable OBJECT-TYPE
			SYNTAX AlarmEnable
			MAX-ACCESS read-write
			STATUS current
			DESCRIPTION
				"Indicates that the format of the received reference is different from expected Trap Enable"
		::= { htg2000c01v1Entry 176 }

		-- 1.3.6.1.4.1.10106.3.101291.1.1.177
		htg2000c01v1RefLockFail OBJECT-TYPE
			SYNTAX BitFail
			MAX-ACCESS read-only
			STATUS current
			DESCRIPTION
				"Indicates that the module is not locked to the reference"
		::= { htg2000c01v1Entry 177 }

		-- 1.3.6.1.4.1.10106.3.101291.1.1.178
		htg2000c01v1RefLockFailTrapEnable OBJECT-TYPE
			SYNTAX AlarmEnable
			MAX-ACCESS read-write
			STATUS current
			DESCRIPTION
				"Indicates that the module is not locked to the reference Trap Enable"
		::= { htg2000c01v1Entry 178 }

		-- 1.3.6.1.4.1.10106.3.101291.1.1.179
		htg2000c01v1DrefCrcFail OBJECT-TYPE
			SYNTAX BitFail
			MAX-ACCESS read-only
			STATUS current
			DESCRIPTION
				"Indicates that the digital reference has CRC/EDH errors"
		::= { htg2000c01v1Entry 179 }

		-- 1.3.6.1.4.1.10106.3.101291.1.1.180
		htg2000c01v1DrefCrcFailTrapEnable OBJECT-TYPE
			SYNTAX AlarmEnable
			MAX-ACCESS read-write
			STATUS current
			DESCRIPTION
				"Indicates that the digital reference has CRC/EDH errors Trap Enable"
		::= { htg2000c01v1Entry 180 }

		-- 1.3.6.1.4.1.10106.3.101291.1.1.181
		htg2000c01v1ArefFormat OBJECT-TYPE
			SYNTAX SdiHd3gFmt3
			MAX-ACCESS read-only
			STATUS current
			DESCRIPTION
				"Indicates the detected format of the analog reference"
		::= { htg2000c01v1Entry 181 }

		-- 1.3.6.1.4.1.10106.3.101291.1.1.182
		htg2000c01v1ArefFormatTrapEnable OBJECT-TYPE
			SYNTAX AlarmEnable
			MAX-ACCESS read-write
			STATUS current
			DESCRIPTION
				"Indicates the detected format of the analog reference Trap Enable"
		::= { htg2000c01v1Entry 182 }

		-- 1.3.6.1.4.1.10106.3.101291.1.1.183
		htg2000c01v1DrefFormat OBJECT-TYPE
			SYNTAX SdiHd3gFmt3
			MAX-ACCESS read-only
			STATUS current
			DESCRIPTION
				"Indicates the detected format of the digital reference"
		::= { htg2000c01v1Entry 183 }

		-- 1.3.6.1.4.1.10106.3.101291.1.1.184
		htg2000c01v1DrefFormatTrapEnable OBJECT-TYPE
			SYNTAX AlarmEnable
			MAX-ACCESS read-write
			STATUS current
			DESCRIPTION
				"Indicates the detected format of the digital reference Trap Enable"
		::= { htg2000c01v1Entry 184 }

		-- 1.3.6.1.4.1.10106.3.101291.1.1.185
		htg2000c01v1MeasDelay OBJECT-TYPE
			SYNTAX DelayX74Ns
			MAX-ACCESS read-only
			STATUS current
			DESCRIPTION
				"Indicates the delay measured between references"
		::= { htg2000c01v1Entry 185 }

		-- 1.3.6.1.4.1.10106.3.101291.1.1.187
		htg2000c01v1MeasFreq OBJECT-TYPE
			SYNTAX FrqDrft3
			MAX-ACCESS read-only
			STATUS current
			DESCRIPTION
				"Indicates the measured frequency deviation"
		::= { htg2000c01v1Entry 187 }

		-- 1.3.6.1.4.1.10106.3.101291.1.1.189
		htg2000c01v1SerialNo OBJECT-TYPE
			SYNTAX SerialNo
			MAX-ACCESS read-only
			STATUS current
			DESCRIPTION
				"Serial number"
		::= { htg2000c01v1Entry 189 }

		-- 1.3.6.1.4.1.10106.3.454502
		htg2000c01v2 OBJECT IDENTIFIER ::= { albalaProducts 454502 }

		-- 1.3.6.1.4.1.10106.3.454502.1
		htg2000c01v2Table  OBJECT-TYPE
			SYNTAX SEQUENCE OF Htg2000c01v2Entry
			MAX-ACCESS not-accessible
			STATUS current
			DESCRIPTION
				"Module  HTG2000C01V2 Table"
			::= { htg2000c01v2 1 }

		-- 1.3.6.1.4.1.10106.3.454502.1.1
		htg2000c01v2Entry  OBJECT-TYPE
			SYNTAX Htg2000c01v2Entry
			MAX-ACCESS not-accessible
			STATUS current
			DESCRIPTION
				"Module HTG2000C01V2 Entry"
			INDEX { htg2000c01v2Index }
			::= { htg2000c01v2Table 1 }

			Htg2000c01v2Entry ::=
			SEQUENCE {
				htg2000c01v2Index
				ModuleIndex,
				htg2000c01v2ActivePreset
				Preset16Active,
				htg2000c01v2LoadPreset
				Preset16Load,
				htg2000c01v2SavePreset
				Preset16Save,
				htg2000c01v2ExpRefFormat
				SdiHd3gFmt6,
				htg2000c01v2ExpRefFormatTrapEnable
				AlarmEnable,
				htg2000c01v2RefInput
				RefSel1,
				htg2000c01v2RefInputTrapEnable
				AlarmEnable,
				htg2000c01v2MeasInput
				RefSel1,
				htg2000c01v2OutFormat1
				SdiHd3gFmt6,
				htg2000c01v2OutFormat1TrapEnable
				AlarmEnable,
				htg2000c01v2OutMute1
				Bit0No1Yes,
				htg2000c01v2HDelay1
				DelayPixel4,
				htg2000c01v2VDelay1
				DelayLines2,
				htg2000c01v2TestSignal1
				Uint5,
				htg2000c01v2EnGrp1Aud1
				Bit0No1Yes,
				htg2000c01v2EnGrp2Aud1
				Bit0No1Yes,
				htg2000c01v2EnGrp3Aud1
				Bit0No1Yes,
				htg2000c01v2EnGrp4Aud1
				Bit0No1Yes,
				htg2000c01v2EnOsd1
				Bit0No1Yes,
				htg2000c01v2AudFrP0G01
				AudioFreq1,
				htg2000c01v2AudFrP1G01
				AudioFreq1,
				htg2000c01v2AudFrP0G11
				AudioFreq1,
				htg2000c01v2AudFrP1G11
				AudioFreq1,
				htg2000c01v2AudFrP0G21
				AudioFreq1,
				htg2000c01v2AudFrP1G21
				AudioFreq1,
				htg2000c01v2AudFrP0G31
				AudioFreq1,
				htg2000c01v2AudFrP1G31
				AudioFreq1,
				htg2000c01v2AudDipP0G01
				Bit0Dis1Ena,
				htg2000c01v2AudDipP1G01
				Bit0Dis1Ena,
				htg2000c01v2AudDipP0G11
				Bit0Dis1Ena,
				htg2000c01v2AudDipP1G11
				Bit0Dis1Ena,
				htg2000c01v2AudDipP0G21
				Bit0Dis1Ena,
				htg2000c01v2AudDipP1G21
				Bit0Dis1Ena,
				htg2000c01v2AudDipP0G31
				Bit0Dis1Ena,
				htg2000c01v2AudDipP1G31
				Bit0Dis1Ena,
				htg2000c01v2AudLevP0G01
				AudioLev0,
				htg2000c01v2AudLevP0G11
				AudioLev0,
				htg2000c01v2AudLevP1G01
				AudioLev0,
				htg2000c01v2AudLevP1G11
				AudioLev0,
				htg2000c01v2AudLevP0G21
				AudioLev0,
				htg2000c01v2AudLevP1G21
				AudioLev0,
				htg2000c01v2AudLevP0G31
				AudioLev0,
				htg2000c01v2AudLevP1G31
				AudioLev0,
				htg2000c01v2OutFormat2
				SdiHd3gFmt6,
				htg2000c01v2OutFormat2TrapEnable
				AlarmEnable,
				htg2000c01v2OutMute2
				Bit0No1Yes,
				htg2000c01v2HDelay2
				DelayPixel4,
				htg2000c01v2VDelay2
				DelayLines2,
				htg2000c01v2TestSignal2
				Uint5,
				htg2000c01v2EnGrp1Aud2
				Bit0No1Yes,
				htg2000c01v2EnGrp2Aud2
				Bit0No1Yes,
				htg2000c01v2EnGrp3Aud2
				Bit0No1Yes,
				htg2000c01v2EnGrp4Aud2
				Bit0No1Yes,
				htg2000c01v2EnOsd2
				Bit0No1Yes,
				htg2000c01v2AudFrP0G02
				AudioFreq1,
				htg2000c01v2AudFrP1G02
				AudioFreq1,
				htg2000c01v2AudFrP0G12
				AudioFreq1,
				htg2000c01v2AudFrP1G12
				AudioFreq1,
				htg2000c01v2AudFrP0G22
				AudioFreq1,
				htg2000c01v2AudFrP1G22
				AudioFreq1,
				htg2000c01v2AudFrP0G32
				AudioFreq1,
				htg2000c01v2AudFrP1G32
				AudioFreq1,
				htg2000c01v2AudDipP0G02
				Bit0Dis1Ena,
				htg2000c01v2AudDipP1G02
				Bit0Dis1Ena,
				htg2000c01v2AudDipP0G12
				Bit0Dis1Ena,
				htg2000c01v2AudDipP1G12
				Bit0Dis1Ena,
				htg2000c01v2AudDipP0G22
				Bit0Dis1Ena,
				htg2000c01v2AudDipP1G22
				Bit0Dis1Ena,
				htg2000c01v2AudDipP0G32
				Bit0Dis1Ena,
				htg2000c01v2AudDipP1G32
				Bit0Dis1Ena,
				htg2000c01v2AudLevP0G02
				AudioLev0,
				htg2000c01v2AudLevP0G12
				AudioLev0,
				htg2000c01v2AudLevP1G02
				AudioLev0,
				htg2000c01v2AudLevP1G12
				AudioLev0,
				htg2000c01v2AudLevP0G22
				AudioLev0,
				htg2000c01v2AudLevP1G22
				AudioLev0,
				htg2000c01v2AudLevP0G32
				AudioLev0,
				htg2000c01v2AudLevP1G32
				AudioLev0,
				htg2000c01v2OutFormat3
				SdiHd3gFmt6,
				htg2000c01v2OutFormat3TrapEnable
				AlarmEnable,
				htg2000c01v2HDelay3
				DelayX74Ns,
				htg2000c01v2VDelay3
				DelayLines2,
				htg2000c01v2Sch3
				Sch3,
				htg2000c01v2ArefFailMsk
				BitMask,
				htg2000c01v2DrefFailMsk
				BitMask,
				htg2000c01v2IrefFailMsk
				BitMask,
				htg2000c01v2RefIncFailMsk
				BitMask,
				htg2000c01v2RefLckFailMsk
				BitMask,
				htg2000c01v2SumMonthSt
				Month,
				htg2000c01v2SumWeekSt
				WeekOfMonth,
				htg2000c01v2SumWDaySt
				Day,
				htg2000c01v2SumHourSt
				TimeH1,
				htg2000c01v2SumHourOffset
				Int8,
				htg2000c01v2WinMonthSt
				Month,
				htg2000c01v2WinWeekSt
				WeekOfMonth,
				htg2000c01v2WinWDaySt
				Day,
				htg2000c01v2WinHourSt
				TimeH1,
				htg2000c01v2WinHourOffset
				Int8,
				htg2000c01v2EnDlsave
				BitMask,
				htg2000c01v2DropFrame
				BitMask,
				htg2000c01v2Bgf
				BgfBits,
				htg2000c01v2DateFormat
				DateFmt,
				htg2000c01v2EnDateGen
				BitMask,
				htg2000c01v2AdjHourDay
				Uint5,
				htg2000c01v2En1001secRst
				Bit0No1Yes,
				htg2000c01v2ArefFail
				BitFail,
				htg2000c01v2ArefFailTrapEnable
				AlarmEnable,
				htg2000c01v2DrefFail
				BitFail,
				htg2000c01v2DrefFailTrapEnable
				AlarmEnable,
				htg2000c01v2IrefFail
				BitFail,
				htg2000c01v2IrefFailTrapEnable
				AlarmEnable,
				htg2000c01v2RefIncFail
				BitFail,
				htg2000c01v2RefIncFailTrapEnable
				AlarmEnable,
				htg2000c01v2RefLockFail
				BitFail,
				htg2000c01v2RefLockFailTrapEnable
				AlarmEnable,
				htg2000c01v2DrefCrcFail
				BitFail,
				htg2000c01v2DrefCrcFailTrapEnable
				AlarmEnable,
				htg2000c01v2TcFail
				BitFail,
				htg2000c01v2ArefFormat
				SdiHd3gFmt3,
				htg2000c01v2ArefFormatTrapEnable
				AlarmEnable,
				htg2000c01v2DrefFormat
				SdiHd3gFmt3,
				htg2000c01v2DrefFormatTrapEnable
				AlarmEnable,
				htg2000c01v2MeasDelay
				DelayX74Ns,
				htg2000c01v2MeasFreq
				FrqDrft3,
				htg2000c01v2SerialNo
				SerialNo,
				htg2000c01v2VidDip1
				Bit0No1Yes,
				htg2000c01v2VidDip2
				Bit0No1Yes,
				htg2000c01v2OsdDly1
				Bit0No1Yes,
				htg2000c01v2OsdDly2
				Bit0No1Yes,
				htg2000c01v2AvDlyBlack
				LumaUint8,
				htg2000c01v2AvDlySil
				LevelDbfs2x,
				htg2000c01v2DelayG1p0l
				DelayX1Ms,
				htg2000c01v2DelayG1p0r
				DelayX1Ms,
				htg2000c01v2DelayG1p1l
				DelayX1Ms,
				htg2000c01v2DelayG1p1r
				DelayX1Ms,
				htg2000c01v2DelayG2p0l
				DelayX1Ms,
				htg2000c01v2DelayG2p0r
				DelayX1Ms,
				htg2000c01v2DelayG2p1l
				DelayX1Ms,
				htg2000c01v2DelayG2p1r
				DelayX1Ms,
				htg2000c01v2DelayG3p0l
				DelayX1Ms,
				htg2000c01v2DelayG3p0r
				DelayX1Ms,
				htg2000c01v2DelayG3p1l
				DelayX1Ms,
				htg2000c01v2DelayG3p1r
				DelayX1Ms,
				htg2000c01v2DelayG4p0l
				DelayX1Ms,
				htg2000c01v2DelayG4p0r
				DelayX1Ms,
				htg2000c01v2DelayG4p1l
				DelayX1Ms,
				htg2000c01v2DelayG4p1r
				DelayX1Ms,
				htg2000c01v2AvSeqG1p0
				BitFail,
				htg2000c01v2AvSeqG1p1
				BitFail,
				htg2000c01v2AvSeqG2p0
				BitFail,
				htg2000c01v2AvSeqG2p1
				BitFail,
				htg2000c01v2AvSeqG3p0
				BitFail,
				htg2000c01v2AvSeqG3p1
				BitFail,
				htg2000c01v2AvSeqG4p0
				BitFail,
				htg2000c01v2AvSeqG4p1
				BitFail,
				htg2000c01v2AudGrpPres1
				BitFailN,
				htg2000c01v2AudGrpPres2
				BitFailN,
				htg2000c01v2AudGrpPres3
				BitFailN,
				htg2000c01v2AudGrpPres4
				BitFailN,
				htg2000c01v2AvSeqPhase
				Uint8
			 }

		-- 1.3.6.1.4.1.10106.3.101291.1.1.1
		htg2000c01v2Index OBJECT-TYPE
			SYNTAX ModuleIndex
			MAX-ACCESS read-only
			STATUS current
			DESCRIPTION
				"Index of HTG2000C01V2 Table"
		::= { htg2000c01v2Entry 1 }

		-- 1.3.6.1.4.1.10106.3.101291.1.1.3
		htg2000c01v2ActivePreset OBJECT-TYPE
			SYNTAX Preset16Active
			MAX-ACCESS read-only
			STATUS current
			DESCRIPTION
				"Shows the active preset"
		::= { htg2000c01v2Entry 3 }

		-- 1.3.6.1.4.1.10106.3.101291.1.1.5
		htg2000c01v2LoadPreset OBJECT-TYPE
			SYNTAX Preset16Load
			MAX-ACCESS read-write
			STATUS current
			DESCRIPTION
				"Allows loading a preset"
		::= { htg2000c01v2Entry 5 }

		-- 1.3.6.1.4.1.10106.3.101291.1.1.7
		htg2000c01v2SavePreset OBJECT-TYPE
			SYNTAX Preset16Save
			MAX-ACCESS read-write
			STATUS current
			DESCRIPTION
				"Allows saving a preset"
		::= { htg2000c01v2Entry 7 }

		-- 1.3.6.1.4.1.10106.3.101291.1.1.9
		htg2000c01v2ExpRefFormat OBJECT-TYPE
			SYNTAX SdiHd3gFmt6
			MAX-ACCESS read-write
			STATUS current
			DESCRIPTION
				"Allows selecting the expected format of the reference"
		::= { htg2000c01v2Entry 9 }

		-- 1.3.6.1.4.1.10106.3.101291.1.1.10
		htg2000c01v2ExpRefFormatTrapEnable OBJECT-TYPE
			SYNTAX AlarmEnable
			MAX-ACCESS read-write
			STATUS current
			DESCRIPTION
				"Allows selecting the expected format of the reference Trap Enable"
		::= { htg2000c01v2Entry 10 }

		-- 1.3.6.1.4.1.10106.3.101291.1.1.11
		htg2000c01v2RefInput OBJECT-TYPE
			SYNTAX RefSel1
			MAX-ACCESS read-write
			STATUS current
			DESCRIPTION
				"Allows selecting the reference input"
		::= { htg2000c01v2Entry 11 }

		-- 1.3.6.1.4.1.10106.3.101291.1.1.12
		htg2000c01v2RefInputTrapEnable OBJECT-TYPE
			SYNTAX AlarmEnable
			MAX-ACCESS read-write
			STATUS current
			DESCRIPTION
				"Allows selecting the reference input Trap Enable"
		::= { htg2000c01v2Entry 12 }

		-- 1.3.6.1.4.1.10106.3.101291.1.1.13
		htg2000c01v2MeasInput OBJECT-TYPE
			SYNTAX RefSel1
			MAX-ACCESS read-write
			STATUS current
			DESCRIPTION
				"Allows selecting the input used for delay mesaurement"
		::= { htg2000c01v2Entry 13 }

		-- 1.3.6.1.4.1.10106.3.101291.1.1.15
		htg2000c01v2OutFormat1 OBJECT-TYPE
			SYNTAX SdiHd3gFmt6
			MAX-ACCESS read-write
			STATUS current
			DESCRIPTION
				"Allows selecting the output format"
		::= { htg2000c01v2Entry 15 }

		-- 1.3.6.1.4.1.10106.3.101291.1.1.16
		htg2000c01v2OutFormat1TrapEnable OBJECT-TYPE
			SYNTAX AlarmEnable
			MAX-ACCESS read-write
			STATUS current
			DESCRIPTION
				"Allows selecting the output format Trap Enable"
		::= { htg2000c01v2Entry 16 }

		-- 1.3.6.1.4.1.10106.3.101291.1.1.17
		htg2000c01v2OutMute1 OBJECT-TYPE
			SYNTAX Bit0No1Yes
			MAX-ACCESS read-write
			STATUS current
			DESCRIPTION
				"Allows disabling the output"
		::= { htg2000c01v2Entry 17 }

		-- 1.3.6.1.4.1.10106.3.101291.1.1.19
		htg2000c01v2HDelay1 OBJECT-TYPE
			SYNTAX DelayPixel4
			MAX-ACCESS read-write
			STATUS current
			DESCRIPTION
				"Allows adjusting the video horizontal delay of main output"
		::= { htg2000c01v2Entry 19 }

		-- 1.3.6.1.4.1.10106.3.101291.1.1.21
		htg2000c01v2VDelay1 OBJECT-TYPE
			SYNTAX DelayLines2
			MAX-ACCESS read-write
			STATUS current
			DESCRIPTION
				"Allows adjusting the video vertical delay of main output"
		::= { htg2000c01v2Entry 21 }

		-- 1.3.6.1.4.1.10106.3.101291.1.1.23
		htg2000c01v2TestSignal1 OBJECT-TYPE
			SYNTAX Uint5
			MAX-ACCESS read-write
			STATUS current
			DESCRIPTION
				"Allows selecting the generated video signal pattern"
		::= { htg2000c01v2Entry 23 }

		-- 1.3.6.1.4.1.10106.3.101291.1.1.25
		htg2000c01v2EnGrp1Aud1 OBJECT-TYPE
			SYNTAX Bit0No1Yes
			MAX-ACCESS read-write
			STATUS current
			DESCRIPTION
				"Allows inserting group 1 audio packets"
		::= { htg2000c01v2Entry 25 }

		-- 1.3.6.1.4.1.10106.3.101291.1.1.27
		htg2000c01v2EnGrp2Aud1 OBJECT-TYPE
			SYNTAX Bit0No1Yes
			MAX-ACCESS read-write
			STATUS current
			DESCRIPTION
				"Allows inserting group 2 audio packets"
		::= { htg2000c01v2Entry 27 }

		-- 1.3.6.1.4.1.10106.3.101291.1.1.29
		htg2000c01v2EnGrp3Aud1 OBJECT-TYPE
			SYNTAX Bit0No1Yes
			MAX-ACCESS read-write
			STATUS current
			DESCRIPTION
				"Allows inserting group 3 audio packets"
		::= { htg2000c01v2Entry 29 }

		-- 1.3.6.1.4.1.10106.3.101291.1.1.31
		htg2000c01v2EnGrp4Aud1 OBJECT-TYPE
			SYNTAX Bit0No1Yes
			MAX-ACCESS read-write
			STATUS current
			DESCRIPTION
				"Allows inserting group 4 audio packets"
		::= { htg2000c01v2Entry 31 }

		-- 1.3.6.1.4.1.10106.3.101291.1.1.33
		htg2000c01v2EnOsd1 OBJECT-TYPE
			SYNTAX Bit0No1Yes
			MAX-ACCESS read-write
			STATUS current
			DESCRIPTION
				"Allows inserting on sreen display caption"
		::= { htg2000c01v2Entry 33 }

		-- 1.3.6.1.4.1.10106.3.101291.1.1.35
		htg2000c01v2AudFrP0G01 OBJECT-TYPE
			SYNTAX AudioFreq1
			MAX-ACCESS read-write
			STATUS current
			DESCRIPTION
				"Allows selecting the audio signal in pair 0 group 1"
		::= { htg2000c01v2Entry 35 }

		-- 1.3.6.1.4.1.10106.3.101291.1.1.37
		htg2000c01v2AudFrP1G01 OBJECT-TYPE
			SYNTAX AudioFreq1
			MAX-ACCESS read-write
			STATUS current
			DESCRIPTION
				"Allows selecting the audio signal in pair 1 group 1"
		::= { htg2000c01v2Entry 37 }

		-- 1.3.6.1.4.1.10106.3.101291.1.1.39
		htg2000c01v2AudFrP0G11 OBJECT-TYPE
			SYNTAX AudioFreq1
			MAX-ACCESS read-write
			STATUS current
			DESCRIPTION
				"Allows selecting the audio signal in pair 0 group 2"
		::= { htg2000c01v2Entry 39 }

		-- 1.3.6.1.4.1.10106.3.101291.1.1.41
		htg2000c01v2AudFrP1G11 OBJECT-TYPE
			SYNTAX AudioFreq1
			MAX-ACCESS read-write
			STATUS current
			DESCRIPTION
				"Allows selecting the audio signal in pair 1 group 2"
		::= { htg2000c01v2Entry 41 }

		-- 1.3.6.1.4.1.10106.3.101291.1.1.43
		htg2000c01v2AudFrP0G21 OBJECT-TYPE
			SYNTAX AudioFreq1
			MAX-ACCESS read-write
			STATUS current
			DESCRIPTION
				"Allows selecting the audio signal in pair 0 group 3"
		::= { htg2000c01v2Entry 43 }

		-- 1.3.6.1.4.1.10106.3.101291.1.1.45
		htg2000c01v2AudFrP1G21 OBJECT-TYPE
			SYNTAX AudioFreq1
			MAX-ACCESS read-write
			STATUS current
			DESCRIPTION
				"Allows selecting the audio signal in pair 1 group 3"
		::= { htg2000c01v2Entry 45 }

		-- 1.3.6.1.4.1.10106.3.101291.1.1.47
		htg2000c01v2AudFrP0G31 OBJECT-TYPE
			SYNTAX AudioFreq1
			MAX-ACCESS read-write
			STATUS current
			DESCRIPTION
				"Allows selecting the audio signal in pair 0 group 4"
		::= { htg2000c01v2Entry 47 }

		-- 1.3.6.1.4.1.10106.3.101291.1.1.49
		htg2000c01v2AudFrP1G31 OBJECT-TYPE
			SYNTAX AudioFreq1
			MAX-ACCESS read-write
			STATUS current
			DESCRIPTION
				"Allows selecting the audio signal in pair 1 group 4"
		::= { htg2000c01v2Entry 49 }

		-- 1.3.6.1.4.1.10106.3.101291.1.1.51
		htg2000c01v2AudDipP0G01 OBJECT-TYPE
			SYNTAX Bit0Dis1Ena
			MAX-ACCESS read-write
			STATUS current
			DESCRIPTION
				"Allows enabling the insertion of silences for channel identification in pair 0 group 1"
		::= { htg2000c01v2Entry 51 }

		-- 1.3.6.1.4.1.10106.3.101291.1.1.53
		htg2000c01v2AudDipP1G01 OBJECT-TYPE
			SYNTAX Bit0Dis1Ena
			MAX-ACCESS read-write
			STATUS current
			DESCRIPTION
				"Allows enabling the insertion of silences for channel identification in pair 1 group 1"
		::= { htg2000c01v2Entry 53 }

		-- 1.3.6.1.4.1.10106.3.101291.1.1.55
		htg2000c01v2AudDipP0G11 OBJECT-TYPE
			SYNTAX Bit0Dis1Ena
			MAX-ACCESS read-write
			STATUS current
			DESCRIPTION
				"Allows enabling the insertion of silences for channel identification in pair 0 group 2"
		::= { htg2000c01v2Entry 55 }

		-- 1.3.6.1.4.1.10106.3.101291.1.1.57
		htg2000c01v2AudDipP1G11 OBJECT-TYPE
			SYNTAX Bit0Dis1Ena
			MAX-ACCESS read-write
			STATUS current
			DESCRIPTION
				"Allows enabling the insertion of silences for channel identification in pair 1 group 2"
		::= { htg2000c01v2Entry 57 }

		-- 1.3.6.1.4.1.10106.3.101291.1.1.59
		htg2000c01v2AudDipP0G21 OBJECT-TYPE
			SYNTAX Bit0Dis1Ena
			MAX-ACCESS read-write
			STATUS current
			DESCRIPTION
				"Allows enabling the insertion of silences for channel identification in pair 0 group 3"
		::= { htg2000c01v2Entry 59 }

		-- 1.3.6.1.4.1.10106.3.101291.1.1.61
		htg2000c01v2AudDipP1G21 OBJECT-TYPE
			SYNTAX Bit0Dis1Ena
			MAX-ACCESS read-write
			STATUS current
			DESCRIPTION
				"Allows enabling the insertion of silences for channel identification in pair 1 group 3"
		::= { htg2000c01v2Entry 61 }

		-- 1.3.6.1.4.1.10106.3.101291.1.1.63
		htg2000c01v2AudDipP0G31 OBJECT-TYPE
			SYNTAX Bit0Dis1Ena
			MAX-ACCESS read-write
			STATUS current
			DESCRIPTION
				"Allows enabling the insertion of silences for channel identification in pair 0 group 4"
		::= { htg2000c01v2Entry 63 }

		-- 1.3.6.1.4.1.10106.3.101291.1.1.65
		htg2000c01v2AudDipP1G31 OBJECT-TYPE
			SYNTAX Bit0Dis1Ena
			MAX-ACCESS read-write
			STATUS current
			DESCRIPTION
				"Allows enabling the insertion of silences for channel identification in pair 1 group 4"
		::= { htg2000c01v2Entry 65 }

		-- 1.3.6.1.4.1.10106.3.101291.1.1.67
		htg2000c01v2AudLevP0G01 OBJECT-TYPE
			SYNTAX AudioLev0
			MAX-ACCESS read-write
			STATUS current
			DESCRIPTION
				"Allows selecting the audio level in pair 0 group 1"
		::= { htg2000c01v2Entry 67 }

		-- 1.3.6.1.4.1.10106.3.101291.1.1.69
		htg2000c01v2AudLevP0G11 OBJECT-TYPE
			SYNTAX AudioLev0
			MAX-ACCESS read-write
			STATUS current
			DESCRIPTION
				"Allows selecting the audio level in pair 1 group 1"
		::= { htg2000c01v2Entry 69 }

		-- 1.3.6.1.4.1.10106.3.101291.1.1.71
		htg2000c01v2AudLevP1G01 OBJECT-TYPE
			SYNTAX AudioLev0
			MAX-ACCESS read-write
			STATUS current
			DESCRIPTION
				"Allows selecting the audio level in pair 0 group 2"
		::= { htg2000c01v2Entry 71 }

		-- 1.3.6.1.4.1.10106.3.101291.1.1.73
		htg2000c01v2AudLevP1G11 OBJECT-TYPE
			SYNTAX AudioLev0
			MAX-ACCESS read-write
			STATUS current
			DESCRIPTION
				"Allows selecting the audio level in pair 1 group 2"
		::= { htg2000c01v2Entry 73 }

		-- 1.3.6.1.4.1.10106.3.101291.1.1.75
		htg2000c01v2AudLevP0G21 OBJECT-TYPE
			SYNTAX AudioLev0
			MAX-ACCESS read-write
			STATUS current
			DESCRIPTION
				"Allows selecting the audio level in pair 0 group 3"
		::= { htg2000c01v2Entry 75 }

		-- 1.3.6.1.4.1.10106.3.101291.1.1.77
		htg2000c01v2AudLevP1G21 OBJECT-TYPE
			SYNTAX AudioLev0
			MAX-ACCESS read-write
			STATUS current
			DESCRIPTION
				"Allows selecting the audio level in pair 1 group 3"
		::= { htg2000c01v2Entry 77 }

		-- 1.3.6.1.4.1.10106.3.101291.1.1.79
		htg2000c01v2AudLevP0G31 OBJECT-TYPE
			SYNTAX AudioLev0
			MAX-ACCESS read-write
			STATUS current
			DESCRIPTION
				"Allows selecting the audio level in pair 0 group 4"
		::= { htg2000c01v2Entry 79 }

		-- 1.3.6.1.4.1.10106.3.101291.1.1.81
		htg2000c01v2AudLevP1G31 OBJECT-TYPE
			SYNTAX AudioLev0
			MAX-ACCESS read-write
			STATUS current
			DESCRIPTION
				"Allows selecting the audio level in pair 1 group 4"
		::= { htg2000c01v2Entry 81 }

		-- 1.3.6.1.4.1.10106.3.101291.1.1.83
		htg2000c01v2OutFormat2 OBJECT-TYPE
			SYNTAX SdiHd3gFmt6
			MAX-ACCESS read-write
			STATUS current
			DESCRIPTION
				"Allows selecting the output format"
		::= { htg2000c01v2Entry 83 }

		-- 1.3.6.1.4.1.10106.3.101291.1.1.84
		htg2000c01v2OutFormat2TrapEnable OBJECT-TYPE
			SYNTAX AlarmEnable
			MAX-ACCESS read-write
			STATUS current
			DESCRIPTION
				"Allows selecting the output format Trap Enable"
		::= { htg2000c01v2Entry 84 }

		-- 1.3.6.1.4.1.10106.3.101291.1.1.85
		htg2000c01v2OutMute2 OBJECT-TYPE
			SYNTAX Bit0No1Yes
			MAX-ACCESS read-write
			STATUS current
			DESCRIPTION
				"Allows disabling the output"
		::= { htg2000c01v2Entry 85 }

		-- 1.3.6.1.4.1.10106.3.101291.1.1.87
		htg2000c01v2HDelay2 OBJECT-TYPE
			SYNTAX DelayPixel4
			MAX-ACCESS read-write
			STATUS current
			DESCRIPTION
				"Allows adjusting the video horizontal delay of main output"
		::= { htg2000c01v2Entry 87 }

		-- 1.3.6.1.4.1.10106.3.101291.1.1.89
		htg2000c01v2VDelay2 OBJECT-TYPE
			SYNTAX DelayLines2
			MAX-ACCESS read-write
			STATUS current
			DESCRIPTION
				"Allows adjusting the video vertical delay of main output"
		::= { htg2000c01v2Entry 89 }

		-- 1.3.6.1.4.1.10106.3.101291.1.1.91
		htg2000c01v2TestSignal2 OBJECT-TYPE
			SYNTAX Uint5
			MAX-ACCESS read-write
			STATUS current
			DESCRIPTION
				"Allows selecting the generated video signal pattern"
		::= { htg2000c01v2Entry 91 }

		-- 1.3.6.1.4.1.10106.3.101291.1.1.93
		htg2000c01v2EnGrp1Aud2 OBJECT-TYPE
			SYNTAX Bit0No1Yes
			MAX-ACCESS read-write
			STATUS current
			DESCRIPTION
				"Allows inserting group 1 audio packets"
		::= { htg2000c01v2Entry 93 }

		-- 1.3.6.1.4.1.10106.3.101291.1.1.95
		htg2000c01v2EnGrp2Aud2 OBJECT-TYPE
			SYNTAX Bit0No1Yes
			MAX-ACCESS read-write
			STATUS current
			DESCRIPTION
				"Allows inserting group 2 audio packets"
		::= { htg2000c01v2Entry 95 }

		-- 1.3.6.1.4.1.10106.3.101291.1.1.97
		htg2000c01v2EnGrp3Aud2 OBJECT-TYPE
			SYNTAX Bit0No1Yes
			MAX-ACCESS read-write
			STATUS current
			DESCRIPTION
				"Allows inserting group 3 audio packets"
		::= { htg2000c01v2Entry 97 }

		-- 1.3.6.1.4.1.10106.3.101291.1.1.99
		htg2000c01v2EnGrp4Aud2 OBJECT-TYPE
			SYNTAX Bit0No1Yes
			MAX-ACCESS read-write
			STATUS current
			DESCRIPTION
				"Allows inserting group 4 audio packets"
		::= { htg2000c01v2Entry 99 }

		-- 1.3.6.1.4.1.10106.3.101291.1.1.101
		htg2000c01v2EnOsd2 OBJECT-TYPE
			SYNTAX Bit0No1Yes
			MAX-ACCESS read-write
			STATUS current
			DESCRIPTION
				"Allows inserting on sreen display caption"
		::= { htg2000c01v2Entry 101 }

		-- 1.3.6.1.4.1.10106.3.101291.1.1.103
		htg2000c01v2AudFrP0G02 OBJECT-TYPE
			SYNTAX AudioFreq1
			MAX-ACCESS read-write
			STATUS current
			DESCRIPTION
				"Allows selecting the audio signal in pair 0 group 1"
		::= { htg2000c01v2Entry 103 }

		-- 1.3.6.1.4.1.10106.3.101291.1.1.105
		htg2000c01v2AudFrP1G02 OBJECT-TYPE
			SYNTAX AudioFreq1
			MAX-ACCESS read-write
			STATUS current
			DESCRIPTION
				"Allows selecting the audio signal in pair 1 group 1"
		::= { htg2000c01v2Entry 105 }

		-- 1.3.6.1.4.1.10106.3.101291.1.1.107
		htg2000c01v2AudFrP0G12 OBJECT-TYPE
			SYNTAX AudioFreq1
			MAX-ACCESS read-write
			STATUS current
			DESCRIPTION
				"Allows selecting the audio signal in pair 0 group 2"
		::= { htg2000c01v2Entry 107 }

		-- 1.3.6.1.4.1.10106.3.101291.1.1.109
		htg2000c01v2AudFrP1G12 OBJECT-TYPE
			SYNTAX AudioFreq1
			MAX-ACCESS read-write
			STATUS current
			DESCRIPTION
				"Allows selecting the audio signal in pair 1 group 2"
		::= { htg2000c01v2Entry 109 }

		-- 1.3.6.1.4.1.10106.3.101291.1.1.111
		htg2000c01v2AudFrP0G22 OBJECT-TYPE
			SYNTAX AudioFreq1
			MAX-ACCESS read-write
			STATUS current
			DESCRIPTION
				"Allows selecting the audio signal in pair 0 group 3"
		::= { htg2000c01v2Entry 111 }

		-- 1.3.6.1.4.1.10106.3.101291.1.1.113
		htg2000c01v2AudFrP1G22 OBJECT-TYPE
			SYNTAX AudioFreq1
			MAX-ACCESS read-write
			STATUS current
			DESCRIPTION
				"Allows selecting the audio signal in pair 1 group 3"
		::= { htg2000c01v2Entry 113 }

		-- 1.3.6.1.4.1.10106.3.101291.1.1.115
		htg2000c01v2AudFrP0G32 OBJECT-TYPE
			SYNTAX AudioFreq1
			MAX-ACCESS read-write
			STATUS current
			DESCRIPTION
				"Allows selecting the audio signal in pair 0 group 4"
		::= { htg2000c01v2Entry 115 }

		-- 1.3.6.1.4.1.10106.3.101291.1.1.117
		htg2000c01v2AudFrP1G32 OBJECT-TYPE
			SYNTAX AudioFreq1
			MAX-ACCESS read-write
			STATUS current
			DESCRIPTION
				"Allows selecting the audio signal in pair 1 group 4"
		::= { htg2000c01v2Entry 117 }

		-- 1.3.6.1.4.1.10106.3.101291.1.1.119
		htg2000c01v2AudDipP0G02 OBJECT-TYPE
			SYNTAX Bit0Dis1Ena
			MAX-ACCESS read-write
			STATUS current
			DESCRIPTION
				"Allows enabling the insertion of silences for channel identification in pair 0 group 1"
		::= { htg2000c01v2Entry 119 }

		-- 1.3.6.1.4.1.10106.3.101291.1.1.121
		htg2000c01v2AudDipP1G02 OBJECT-TYPE
			SYNTAX Bit0Dis1Ena
			MAX-ACCESS read-write
			STATUS current
			DESCRIPTION
				"Allows enabling the insertion of silences for channel identification in pair 1 group 1"
		::= { htg2000c01v2Entry 121 }

		-- 1.3.6.1.4.1.10106.3.101291.1.1.123
		htg2000c01v2AudDipP0G12 OBJECT-TYPE
			SYNTAX Bit0Dis1Ena
			MAX-ACCESS read-write
			STATUS current
			DESCRIPTION
				"Allows enabling the insertion of silences for channel identification in pair 0 group 2"
		::= { htg2000c01v2Entry 123 }

		-- 1.3.6.1.4.1.10106.3.101291.1.1.125
		htg2000c01v2AudDipP1G12 OBJECT-TYPE
			SYNTAX Bit0Dis1Ena
			MAX-ACCESS read-write
			STATUS current
			DESCRIPTION
				"Allows enabling the insertion of silences for channel identification in pair 1 group 2"
		::= { htg2000c01v2Entry 125 }

		-- 1.3.6.1.4.1.10106.3.101291.1.1.127
		htg2000c01v2AudDipP0G22 OBJECT-TYPE
			SYNTAX Bit0Dis1Ena
			MAX-ACCESS read-write
			STATUS current
			DESCRIPTION
				"Allows enabling the insertion of silences for channel identification in pair 0 group 3"
		::= { htg2000c01v2Entry 127 }

		-- 1.3.6.1.4.1.10106.3.101291.1.1.129
		htg2000c01v2AudDipP1G22 OBJECT-TYPE
			SYNTAX Bit0Dis1Ena
			MAX-ACCESS read-write
			STATUS current
			DESCRIPTION
				"Allows enabling the insertion of silences for channel identification in pair 1 group 3"
		::= { htg2000c01v2Entry 129 }

		-- 1.3.6.1.4.1.10106.3.101291.1.1.131
		htg2000c01v2AudDipP0G32 OBJECT-TYPE
			SYNTAX Bit0Dis1Ena
			MAX-ACCESS read-write
			STATUS current
			DESCRIPTION
				"Allows enabling the insertion of silences for channel identification in pair 0 group 4"
		::= { htg2000c01v2Entry 131 }

		-- 1.3.6.1.4.1.10106.3.101291.1.1.133
		htg2000c01v2AudDipP1G32 OBJECT-TYPE
			SYNTAX Bit0Dis1Ena
			MAX-ACCESS read-write
			STATUS current
			DESCRIPTION
				"Allows enabling the insertion of silences for channel identification in pair 1 group 4"
		::= { htg2000c01v2Entry 133 }

		-- 1.3.6.1.4.1.10106.3.101291.1.1.135
		htg2000c01v2AudLevP0G02 OBJECT-TYPE
			SYNTAX AudioLev0
			MAX-ACCESS read-write
			STATUS current
			DESCRIPTION
				"Allows selecting the audio level in pair 0 group 1"
		::= { htg2000c01v2Entry 135 }

		-- 1.3.6.1.4.1.10106.3.101291.1.1.137
		htg2000c01v2AudLevP0G12 OBJECT-TYPE
			SYNTAX AudioLev0
			MAX-ACCESS read-write
			STATUS current
			DESCRIPTION
				"Allows selecting the audio level in pair 1 group 1"
		::= { htg2000c01v2Entry 137 }

		-- 1.3.6.1.4.1.10106.3.101291.1.1.139
		htg2000c01v2AudLevP1G02 OBJECT-TYPE
			SYNTAX AudioLev0
			MAX-ACCESS read-write
			STATUS current
			DESCRIPTION
				"Allows selecting the audio level in pair 0 group 2"
		::= { htg2000c01v2Entry 139 }

		-- 1.3.6.1.4.1.10106.3.101291.1.1.141
		htg2000c01v2AudLevP1G12 OBJECT-TYPE
			SYNTAX AudioLev0
			MAX-ACCESS read-write
			STATUS current
			DESCRIPTION
				"Allows selecting the audio level in pair 1 group 2"
		::= { htg2000c01v2Entry 141 }

		-- 1.3.6.1.4.1.10106.3.101291.1.1.143
		htg2000c01v2AudLevP0G22 OBJECT-TYPE
			SYNTAX AudioLev0
			MAX-ACCESS read-write
			STATUS current
			DESCRIPTION
				"Allows selecting the audio level in pair 0 group 3"
		::= { htg2000c01v2Entry 143 }

		-- 1.3.6.1.4.1.10106.3.101291.1.1.145
		htg2000c01v2AudLevP1G22 OBJECT-TYPE
			SYNTAX AudioLev0
			MAX-ACCESS read-write
			STATUS current
			DESCRIPTION
				"Allows selecting the audio level in pair 1 group 3"
		::= { htg2000c01v2Entry 145 }

		-- 1.3.6.1.4.1.10106.3.101291.1.1.147
		htg2000c01v2AudLevP0G32 OBJECT-TYPE
			SYNTAX AudioLev0
			MAX-ACCESS read-write
			STATUS current
			DESCRIPTION
				"Allows selecting the audio level in pair 0 group 4"
		::= { htg2000c01v2Entry 147 }

		-- 1.3.6.1.4.1.10106.3.101291.1.1.149
		htg2000c01v2AudLevP1G32 OBJECT-TYPE
			SYNTAX AudioLev0
			MAX-ACCESS read-write
			STATUS current
			DESCRIPTION
				"Allows selecting the audio level in pair 1 group 4"
		::= { htg2000c01v2Entry 149 }

		-- 1.3.6.1.4.1.10106.3.101291.1.1.151
		htg2000c01v2OutFormat3 OBJECT-TYPE
			SYNTAX SdiHd3gFmt6
			MAX-ACCESS read-write
			STATUS current
			DESCRIPTION
				"Allows selecting the output format"
		::= { htg2000c01v2Entry 151 }

		-- 1.3.6.1.4.1.10106.3.101291.1.1.152
		htg2000c01v2OutFormat3TrapEnable OBJECT-TYPE
			SYNTAX AlarmEnable
			MAX-ACCESS read-write
			STATUS current
			DESCRIPTION
				"Allows selecting the output format Trap Enable"
		::= { htg2000c01v2Entry 152 }

		-- 1.3.6.1.4.1.10106.3.101291.1.1.153
		htg2000c01v2HDelay3 OBJECT-TYPE
			SYNTAX DelayX74Ns
			MAX-ACCESS read-write
			STATUS current
			DESCRIPTION
				"Allows adjusting the video horizontal delay of main output"
		::= { htg2000c01v2Entry 153 }

		-- 1.3.6.1.4.1.10106.3.101291.1.1.155
		htg2000c01v2VDelay3 OBJECT-TYPE
			SYNTAX DelayLines2
			MAX-ACCESS read-write
			STATUS current
			DESCRIPTION
				"Allows adjusting the video vertical delay of main output"
		::= { htg2000c01v2Entry 155 }

		-- 1.3.6.1.4.1.10106.3.101291.1.1.157
		htg2000c01v2Sch3 OBJECT-TYPE
			SYNTAX Sch3
			MAX-ACCESS read-write
			STATUS current
			DESCRIPTION
				"Allows adjusting the SCH"
		::= { htg2000c01v2Entry 157 }

		-- 1.3.6.1.4.1.10106.3.101291.1.1.159
		htg2000c01v2ArefFailMsk OBJECT-TYPE
			SYNTAX BitMask
			MAX-ACCESS read-write
			STATUS current
			DESCRIPTION
				"Allows masking the analog reference absence fail"
		::= { htg2000c01v2Entry 159 }

		-- 1.3.6.1.4.1.10106.3.101291.1.1.161
		htg2000c01v2DrefFailMsk OBJECT-TYPE
			SYNTAX BitMask
			MAX-ACCESS read-write
			STATUS current
			DESCRIPTION
				"Allows masking the digital reference absence fail"
		::= { htg2000c01v2Entry 161 }

		-- 1.3.6.1.4.1.10106.3.101291.1.1.163
		htg2000c01v2IrefFailMsk OBJECT-TYPE
			SYNTAX BitMask
			MAX-ACCESS read-write
			STATUS current
			DESCRIPTION
				"Allows masking the internal reference absence fail"
		::= { htg2000c01v2Entry 163 }

		-- 1.3.6.1.4.1.10106.3.101291.1.1.165
		htg2000c01v2RefIncFailMsk OBJECT-TYPE
			SYNTAX BitMask
			MAX-ACCESS read-write
			STATUS current
			DESCRIPTION
				"Allows masking the different reference format fail"
		::= { htg2000c01v2Entry 165 }

		-- 1.3.6.1.4.1.10106.3.101291.1.1.167
		htg2000c01v2RefLckFailMsk OBJECT-TYPE
			SYNTAX BitMask
			MAX-ACCESS read-write
			STATUS current
			DESCRIPTION
				"Allows masking the reference lock fail"
		::= { htg2000c01v2Entry 167 }

		-- 1.3.6.1.4.1.10106.3.101291.1.1.169
		htg2000c01v2SumMonthSt OBJECT-TYPE
			SYNTAX Month
			MAX-ACCESS read-write
			STATUS current
			DESCRIPTION
				"It allows selecting the month when summer time starts"
		::= { htg2000c01v2Entry 169 }

		-- 1.3.6.1.4.1.10106.3.101291.1.1.171
		htg2000c01v2SumWeekSt OBJECT-TYPE
			SYNTAX WeekOfMonth
			MAX-ACCESS read-write
			STATUS current
			DESCRIPTION
				"It allows selecting the week of the month when summer time starts"
		::= { htg2000c01v2Entry 171 }

		-- 1.3.6.1.4.1.10106.3.101291.1.1.173
		htg2000c01v2SumWDaySt OBJECT-TYPE
			SYNTAX Day
			MAX-ACCESS read-write
			STATUS current
			DESCRIPTION
				"It allows selecting the week day when summer time starts"
		::= { htg2000c01v2Entry 173 }

		-- 1.3.6.1.4.1.10106.3.101291.1.1.175
		htg2000c01v2SumHourSt OBJECT-TYPE
			SYNTAX TimeH1
			MAX-ACCESS read-write
			STATUS current
			DESCRIPTION
				"It allows selecting the UTC hour when summer time starts"
		::= { htg2000c01v2Entry 175 }

		-- 1.3.6.1.4.1.10106.3.101291.1.1.177
		htg2000c01v2SumHourOffset OBJECT-TYPE
			SYNTAX Int8
			MAX-ACCESS read-write
			STATUS current
			DESCRIPTION
				"It allows selecting the local time offset at summer time"
		::= { htg2000c01v2Entry 177 }

		-- 1.3.6.1.4.1.10106.3.101291.1.1.179
		htg2000c01v2WinMonthSt OBJECT-TYPE
			SYNTAX Month
			MAX-ACCESS read-write
			STATUS current
			DESCRIPTION
				"It allows selecting the month when winter time starts"
		::= { htg2000c01v2Entry 179 }

		-- 1.3.6.1.4.1.10106.3.101291.1.1.181
		htg2000c01v2WinWeekSt OBJECT-TYPE
			SYNTAX WeekOfMonth
			MAX-ACCESS read-write
			STATUS current
			DESCRIPTION
				"It allows selecting the week of the month when winter time starts"
		::= { htg2000c01v2Entry 181 }

		-- 1.3.6.1.4.1.10106.3.101291.1.1.183
		htg2000c01v2WinWDaySt OBJECT-TYPE
			SYNTAX Day
			MAX-ACCESS read-write
			STATUS current
			DESCRIPTION
				"It allows selecting the week day when winter time starts"
		::= { htg2000c01v2Entry 183 }

		-- 1.3.6.1.4.1.10106.3.101291.1.1.185
		htg2000c01v2WinHourSt OBJECT-TYPE
			SYNTAX TimeH1
			MAX-ACCESS read-write
			STATUS current
			DESCRIPTION
				"It allows selecting the UTC hour when winter time starts"
		::= { htg2000c01v2Entry 185 }

		-- 1.3.6.1.4.1.10106.3.101291.1.1.187
		htg2000c01v2WinHourOffset OBJECT-TYPE
			SYNTAX Int8
			MAX-ACCESS read-write
			STATUS current
			DESCRIPTION
				"It allows selecting the local time offset at winter time"
		::= { htg2000c01v2Entry 187 }

		-- 1.3.6.1.4.1.10106.3.101291.1.1.189
		htg2000c01v2EnDlsave OBJECT-TYPE
			SYNTAX BitMask
			MAX-ACCESS read-write
			STATUS current
			DESCRIPTION
				"It allows enabling automatic daylight saving"
		::= { htg2000c01v2Entry 189 }

		-- 1.3.6.1.4.1.10106.3.101291.1.1.191
		htg2000c01v2DropFrame OBJECT-TYPE
			SYNTAX BitMask
			MAX-ACCESS read-write
			STATUS current
			DESCRIPTION
				"Enables time compensated mode in 59.94 Hz formats"
		::= { htg2000c01v2Entry 191 }

		-- 1.3.6.1.4.1.10106.3.101291.1.1.193
		htg2000c01v2Bgf OBJECT-TYPE
			SYNTAX BgfBits
			MAX-ACCESS read-write
			STATUS current
			DESCRIPTION
				"Contents of the binary group flags in the time code"
		::= { htg2000c01v2Entry 193 }

		-- 1.3.6.1.4.1.10106.3.101291.1.1.195
		htg2000c01v2DateFormat OBJECT-TYPE
			SYNTAX DateFmt
			MAX-ACCESS read-write
			STATUS current
			DESCRIPTION
				"Selects date format in the BGF (binary group flags)"
		::= { htg2000c01v2Entry 195 }

		-- 1.3.6.1.4.1.10106.3.101291.1.1.197
		htg2000c01v2EnDateGen OBJECT-TYPE
			SYNTAX BitMask
			MAX-ACCESS read-write
			STATUS current
			DESCRIPTION
				"Enables date insertion in time code"
		::= { htg2000c01v2Entry 197 }

		-- 1.3.6.1.4.1.10106.3.101291.1.1.199
		htg2000c01v2AdjHourDay OBJECT-TYPE
			SYNTAX Uint5
			MAX-ACCESS read-write
			STATUS current
			DESCRIPTION
				"Resets time code frame counter value at the end of this UTC hour (59.94 Hz formats only)"
		::= { htg2000c01v2Entry 199 }

		-- 1.3.6.1.4.1.10106.3.101291.1.1.201
		htg2000c01v2En1001secRst OBJECT-TYPE
			SYNTAX Bit0No1Yes
			MAX-ACCESS read-write
			STATUS current
			DESCRIPTION
				"Compensates for time code drift with respect to UTC time (59.94 Hz formats only)"
		::= { htg2000c01v2Entry 201 }

		-- 1.3.6.1.4.1.10106.3.101291.1.1.203
		htg2000c01v2ArefFail OBJECT-TYPE
			SYNTAX BitFail
			MAX-ACCESS read-only
			STATUS current
			DESCRIPTION
				"Indicates the absence of analog reference"
		::= { htg2000c01v2Entry 203 }

		-- 1.3.6.1.4.1.10106.3.101291.1.1.204
		htg2000c01v2ArefFailTrapEnable OBJECT-TYPE
			SYNTAX AlarmEnable
			MAX-ACCESS read-write
			STATUS current
			DESCRIPTION
				"Indicates the absence of analog reference Trap Enable"
		::= { htg2000c01v2Entry 204 }

		-- 1.3.6.1.4.1.10106.3.101291.1.1.205
		htg2000c01v2DrefFail OBJECT-TYPE
			SYNTAX BitFail
			MAX-ACCESS read-only
			STATUS current
			DESCRIPTION
				"Indicates the absence of digital reference"
		::= { htg2000c01v2Entry 205 }

		-- 1.3.6.1.4.1.10106.3.101291.1.1.206
		htg2000c01v2DrefFailTrapEnable OBJECT-TYPE
			SYNTAX AlarmEnable
			MAX-ACCESS read-write
			STATUS current
			DESCRIPTION
				"Indicates the absence of digital reference Trap Enable"
		::= { htg2000c01v2Entry 206 }

		-- 1.3.6.1.4.1.10106.3.101291.1.1.207
		htg2000c01v2IrefFail OBJECT-TYPE
			SYNTAX BitFail
			MAX-ACCESS read-only
			STATUS current
			DESCRIPTION
				"Indicates the absence of internal reference"
		::= { htg2000c01v2Entry 207 }

		-- 1.3.6.1.4.1.10106.3.101291.1.1.208
		htg2000c01v2IrefFailTrapEnable OBJECT-TYPE
			SYNTAX AlarmEnable
			MAX-ACCESS read-write
			STATUS current
			DESCRIPTION
				"Indicates the absence of internal reference Trap Enable"
		::= { htg2000c01v2Entry 208 }

		-- 1.3.6.1.4.1.10106.3.101291.1.1.209
		htg2000c01v2RefIncFail OBJECT-TYPE
			SYNTAX BitFail
			MAX-ACCESS read-only
			STATUS current
			DESCRIPTION
				"Indicates that the format of the received reference is different from expected"
		::= { htg2000c01v2Entry 209 }

		-- 1.3.6.1.4.1.10106.3.101291.1.1.210
		htg2000c01v2RefIncFailTrapEnable OBJECT-TYPE
			SYNTAX AlarmEnable
			MAX-ACCESS read-write
			STATUS current
			DESCRIPTION
				"Indicates that the format of the received reference is different from expected Trap Enable"
		::= { htg2000c01v2Entry 210 }

		-- 1.3.6.1.4.1.10106.3.101291.1.1.211
		htg2000c01v2RefLockFail OBJECT-TYPE
			SYNTAX BitFail
			MAX-ACCESS read-only
			STATUS current
			DESCRIPTION
				"Indicates that the module is not locked to the reference"
		::= { htg2000c01v2Entry 211 }

		-- 1.3.6.1.4.1.10106.3.101291.1.1.212
		htg2000c01v2RefLockFailTrapEnable OBJECT-TYPE
			SYNTAX AlarmEnable
			MAX-ACCESS read-write
			STATUS current
			DESCRIPTION
				"Indicates that the module is not locked to the reference Trap Enable"
		::= { htg2000c01v2Entry 212 }

		-- 1.3.6.1.4.1.10106.3.101291.1.1.213
		htg2000c01v2DrefCrcFail OBJECT-TYPE
			SYNTAX BitFail
			MAX-ACCESS read-only
			STATUS current
			DESCRIPTION
				"Indicates that the digital reference has CRC/EDH errors"
		::= { htg2000c01v2Entry 213 }

		-- 1.3.6.1.4.1.10106.3.101291.1.1.214
		htg2000c01v2DrefCrcFailTrapEnable OBJECT-TYPE
			SYNTAX AlarmEnable
			MAX-ACCESS read-write
			STATUS current
			DESCRIPTION
				"Indicates that the digital reference has CRC/EDH errors Trap Enable"
		::= { htg2000c01v2Entry 214 }

		-- 1.3.6.1.4.1.10106.3.101291.1.1.215
		htg2000c01v2TcFail OBJECT-TYPE
			SYNTAX BitFail
			MAX-ACCESS read-only
			STATUS current
			DESCRIPTION
				"Indicates the absence of time and date information in the internal reference"
		::= { htg2000c01v2Entry 215 }

		-- 1.3.6.1.4.1.10106.3.101291.1.1.217
		htg2000c01v2ArefFormat OBJECT-TYPE
			SYNTAX SdiHd3gFmt3
			MAX-ACCESS read-only
			STATUS current
			DESCRIPTION
				"Indicates the detected format of the analog reference"
		::= { htg2000c01v2Entry 217 }

		-- 1.3.6.1.4.1.10106.3.101291.1.1.218
		htg2000c01v2ArefFormatTrapEnable OBJECT-TYPE
			SYNTAX AlarmEnable
			MAX-ACCESS read-write
			STATUS current
			DESCRIPTION
				"Indicates the detected format of the analog reference Trap Enable"
		::= { htg2000c01v2Entry 218 }

		-- 1.3.6.1.4.1.10106.3.101291.1.1.219
		htg2000c01v2DrefFormat OBJECT-TYPE
			SYNTAX SdiHd3gFmt3
			MAX-ACCESS read-only
			STATUS current
			DESCRIPTION
				"Indicates the detected format of the digital reference"
		::= { htg2000c01v2Entry 219 }

		-- 1.3.6.1.4.1.10106.3.101291.1.1.220
		htg2000c01v2DrefFormatTrapEnable OBJECT-TYPE
			SYNTAX AlarmEnable
			MAX-ACCESS read-write
			STATUS current
			DESCRIPTION
				"Indicates the detected format of the digital reference Trap Enable"
		::= { htg2000c01v2Entry 220 }

		-- 1.3.6.1.4.1.10106.3.101291.1.1.221
		htg2000c01v2MeasDelay OBJECT-TYPE
			SYNTAX DelayX74Ns
			MAX-ACCESS read-only
			STATUS current
			DESCRIPTION
				"Indicates the delay measured between references"
		::= { htg2000c01v2Entry 221 }

		-- 1.3.6.1.4.1.10106.3.101291.1.1.223
		htg2000c01v2MeasFreq OBJECT-TYPE
			SYNTAX FrqDrft3
			MAX-ACCESS read-only
			STATUS current
			DESCRIPTION
				"Indicates the measured frequency deviation"
		::= { htg2000c01v2Entry 223 }

		-- 1.3.6.1.4.1.10106.3.101291.1.1.225
		htg2000c01v2SerialNo OBJECT-TYPE
			SYNTAX SerialNo
			MAX-ACCESS read-only
			STATUS current
			DESCRIPTION
				"Serial number"
		::= { htg2000c01v2Entry 225 }

		-- 1.3.6.1.4.1.10106.3.101291.1.1.261
		htg2000c01v2VidDip1 OBJECT-TYPE
			SYNTAX Bit0No1Yes
			MAX-ACCESS read-write
			STATUS current
			DESCRIPTION
				"Black in audio ID silences"
		::= { htg2000c01v2Entry 261 }

		-- 1.3.6.1.4.1.10106.3.101291.1.1.263
		htg2000c01v2VidDip2 OBJECT-TYPE
			SYNTAX Bit0No1Yes
			MAX-ACCESS read-write
			STATUS current
			DESCRIPTION
				"Black in audio ID silences"
		::= { htg2000c01v2Entry 263 }

		-- 1.3.6.1.4.1.10106.3.101291.1.1.265
		htg2000c01v2OsdDly1 OBJECT-TYPE
			SYNTAX Bit0No1Yes
			MAX-ACCESS read-write
			STATUS current
			DESCRIPTION
				"Shows A/V delays instead of the specified texts"
		::= { htg2000c01v2Entry 265 }

		-- 1.3.6.1.4.1.10106.3.101291.1.1.267
		htg2000c01v2OsdDly2 OBJECT-TYPE
			SYNTAX Bit0No1Yes
			MAX-ACCESS read-write
			STATUS current
			DESCRIPTION
				"Shows A/V delays instead of the specified texts"
		::= { htg2000c01v2Entry 267 }

		-- 1.3.6.1.4.1.10106.3.101291.1.1.269
		htg2000c01v2AvDlyBlack OBJECT-TYPE
			SYNTAX LumaUint8
			MAX-ACCESS read-write
			STATUS current
			DESCRIPTION
				"Maximum luminance value accepted for black frame detection"
		::= { htg2000c01v2Entry 269 }

		-- 1.3.6.1.4.1.10106.3.101291.1.1.271
		htg2000c01v2AvDlySil OBJECT-TYPE
			SYNTAX LevelDbfs2x
			MAX-ACCESS read-write
			STATUS current
			DESCRIPTION
				"Maximum audio level accepted for silence detection"
		::= { htg2000c01v2Entry 271 }

		-- 1.3.6.1.4.1.10106.3.101291.1.1.273
		htg2000c01v2DelayG1p0l OBJECT-TYPE
			SYNTAX DelayX1Ms
			MAX-ACCESS read-only
			STATUS current
			DESCRIPTION
				"A negative value implies that audio is advanced with respect to video"
		::= { htg2000c01v2Entry 273 }

		-- 1.3.6.1.4.1.10106.3.101291.1.1.275
		htg2000c01v2DelayG1p0r OBJECT-TYPE
			SYNTAX DelayX1Ms
			MAX-ACCESS read-only
			STATUS current
			DESCRIPTION
				"A negative value implies that audio is advanced with respect to video"
		::= { htg2000c01v2Entry 275 }

		-- 1.3.6.1.4.1.10106.3.101291.1.1.277
		htg2000c01v2DelayG1p1l OBJECT-TYPE
			SYNTAX DelayX1Ms
			MAX-ACCESS read-only
			STATUS current
			DESCRIPTION
				"A negative value implies that audio is advanced with respect to video"
		::= { htg2000c01v2Entry 277 }

		-- 1.3.6.1.4.1.10106.3.101291.1.1.279
		htg2000c01v2DelayG1p1r OBJECT-TYPE
			SYNTAX DelayX1Ms
			MAX-ACCESS read-only
			STATUS current
			DESCRIPTION
				"A negative value implies that audio is advanced with respect to video"
		::= { htg2000c01v2Entry 279 }

		-- 1.3.6.1.4.1.10106.3.101291.1.1.281
		htg2000c01v2DelayG2p0l OBJECT-TYPE
			SYNTAX DelayX1Ms
			MAX-ACCESS read-only
			STATUS current
			DESCRIPTION
				"A negative value implies that audio is advanced with respect to video"
		::= { htg2000c01v2Entry 281 }

		-- 1.3.6.1.4.1.10106.3.101291.1.1.283
		htg2000c01v2DelayG2p0r OBJECT-TYPE
			SYNTAX DelayX1Ms
			MAX-ACCESS read-only
			STATUS current
			DESCRIPTION
				"A negative value implies that audio is advanced with respect to video"
		::= { htg2000c01v2Entry 283 }

		-- 1.3.6.1.4.1.10106.3.101291.1.1.285
		htg2000c01v2DelayG2p1l OBJECT-TYPE
			SYNTAX DelayX1Ms
			MAX-ACCESS read-only
			STATUS current
			DESCRIPTION
				"A negative value implies that audio is advanced with respect to video"
		::= { htg2000c01v2Entry 285 }

		-- 1.3.6.1.4.1.10106.3.101291.1.1.287
		htg2000c01v2DelayG2p1r OBJECT-TYPE
			SYNTAX DelayX1Ms
			MAX-ACCESS read-only
			STATUS current
			DESCRIPTION
				"A negative value implies that audio is advanced with respect to video"
		::= { htg2000c01v2Entry 287 }

		-- 1.3.6.1.4.1.10106.3.101291.1.1.289
		htg2000c01v2DelayG3p0l OBJECT-TYPE
			SYNTAX DelayX1Ms
			MAX-ACCESS read-only
			STATUS current
			DESCRIPTION
				"A negative value implies that audio is advanced with respect to video"
		::= { htg2000c01v2Entry 289 }

		-- 1.3.6.1.4.1.10106.3.101291.1.1.291
		htg2000c01v2DelayG3p0r OBJECT-TYPE
			SYNTAX DelayX1Ms
			MAX-ACCESS read-only
			STATUS current
			DESCRIPTION
				"A negative value implies that audio is advanced with respect to video"
		::= { htg2000c01v2Entry 291 }

		-- 1.3.6.1.4.1.10106.3.101291.1.1.293
		htg2000c01v2DelayG3p1l OBJECT-TYPE
			SYNTAX DelayX1Ms
			MAX-ACCESS read-only
			STATUS current
			DESCRIPTION
				"A negative value implies that audio is advanced with respect to video"
		::= { htg2000c01v2Entry 293 }

		-- 1.3.6.1.4.1.10106.3.101291.1.1.295
		htg2000c01v2DelayG3p1r OBJECT-TYPE
			SYNTAX DelayX1Ms
			MAX-ACCESS read-only
			STATUS current
			DESCRIPTION
				"A negative value implies that audio is advanced with respect to video"
		::= { htg2000c01v2Entry 295 }

		-- 1.3.6.1.4.1.10106.3.101291.1.1.297
		htg2000c01v2DelayG4p0l OBJECT-TYPE
			SYNTAX DelayX1Ms
			MAX-ACCESS read-only
			STATUS current
			DESCRIPTION
				"A negative value implies that audio is advanced with respect to video"
		::= { htg2000c01v2Entry 297 }

		-- 1.3.6.1.4.1.10106.3.101291.1.1.299
		htg2000c01v2DelayG4p0r OBJECT-TYPE
			SYNTAX DelayX1Ms
			MAX-ACCESS read-only
			STATUS current
			DESCRIPTION
				"A negative value implies that audio is advanced with respect to video"
		::= { htg2000c01v2Entry 299 }

		-- 1.3.6.1.4.1.10106.3.101291.1.1.301
		htg2000c01v2DelayG4p1l OBJECT-TYPE
			SYNTAX DelayX1Ms
			MAX-ACCESS read-only
			STATUS current
			DESCRIPTION
				"A negative value implies that audio is advanced with respect to video"
		::= { htg2000c01v2Entry 301 }

		-- 1.3.6.1.4.1.10106.3.101291.1.1.303
		htg2000c01v2DelayG4p1r OBJECT-TYPE
			SYNTAX DelayX1Ms
			MAX-ACCESS read-only
			STATUS current
			DESCRIPTION
				"A negative value implies that audio is advanced with respect to video"
		::= { htg2000c01v2Entry 303 }

		-- 1.3.6.1.4.1.10106.3.101291.1.1.305
		htg2000c01v2AvSeqG1p0 OBJECT-TYPE
			SYNTAX BitFail
			MAX-ACCESS read-only
			STATUS current
			DESCRIPTION
				"The A/V delay measurement sequence was not correctly detected for this pair"
		::= { htg2000c01v2Entry 305 }

		-- 1.3.6.1.4.1.10106.3.101291.1.1.307
		htg2000c01v2AvSeqG1p1 OBJECT-TYPE
			SYNTAX BitFail
			MAX-ACCESS read-only
			STATUS current
			DESCRIPTION
				"The A/V delay measurement sequence was not correctly detected for this pair"
		::= { htg2000c01v2Entry 307 }

		-- 1.3.6.1.4.1.10106.3.101291.1.1.309
		htg2000c01v2AvSeqG2p0 OBJECT-TYPE
			SYNTAX BitFail
			MAX-ACCESS read-only
			STATUS current
			DESCRIPTION
				"The A/V delay measurement sequence was not correctly detected for this pair"
		::= { htg2000c01v2Entry 309 }

		-- 1.3.6.1.4.1.10106.3.101291.1.1.311
		htg2000c01v2AvSeqG2p1 OBJECT-TYPE
			SYNTAX BitFail
			MAX-ACCESS read-only
			STATUS current
			DESCRIPTION
				"The A/V delay measurement sequence was not correctly detected for this pair"
		::= { htg2000c01v2Entry 311 }

		-- 1.3.6.1.4.1.10106.3.101291.1.1.313
		htg2000c01v2AvSeqG3p0 OBJECT-TYPE
			SYNTAX BitFail
			MAX-ACCESS read-only
			STATUS current
			DESCRIPTION
				"The A/V delay measurement sequence was not correctly detected for this pair"
		::= { htg2000c01v2Entry 313 }

		-- 1.3.6.1.4.1.10106.3.101291.1.1.315
		htg2000c01v2AvSeqG3p1 OBJECT-TYPE
			SYNTAX BitFail
			MAX-ACCESS read-only
			STATUS current
			DESCRIPTION
				"The A/V delay measurement sequence was not correctly detected for this pair"
		::= { htg2000c01v2Entry 315 }

		-- 1.3.6.1.4.1.10106.3.101291.1.1.317
		htg2000c01v2AvSeqG4p0 OBJECT-TYPE
			SYNTAX BitFail
			MAX-ACCESS read-only
			STATUS current
			DESCRIPTION
				"The A/V delay measurement sequence was not correctly detected for this pair"
		::= { htg2000c01v2Entry 317 }

		-- 1.3.6.1.4.1.10106.3.101291.1.1.319
		htg2000c01v2AvSeqG4p1 OBJECT-TYPE
			SYNTAX BitFail
			MAX-ACCESS read-only
			STATUS current
			DESCRIPTION
				"The A/V delay measurement sequence was not correctly detected for this pair"
		::= { htg2000c01v2Entry 319 }

		-- 1.3.6.1.4.1.10106.3.101291.1.1.321
		htg2000c01v2AudGrpPres1 OBJECT-TYPE
			SYNTAX BitFailN
			MAX-ACCESS read-only
			STATUS current
			DESCRIPTION
				"Group 1 present"
		::= { htg2000c01v2Entry 321 }

		-- 1.3.6.1.4.1.10106.3.101291.1.1.323
		htg2000c01v2AudGrpPres2 OBJECT-TYPE
			SYNTAX BitFailN
			MAX-ACCESS read-only
			STATUS current
			DESCRIPTION
				"Group 2 present"
		::= { htg2000c01v2Entry 323 }

		-- 1.3.6.1.4.1.10106.3.101291.1.1.325
		htg2000c01v2AudGrpPres3 OBJECT-TYPE
			SYNTAX BitFailN
			MAX-ACCESS read-only
			STATUS current
			DESCRIPTION
				"Group 3 present"
		::= { htg2000c01v2Entry 325 }

		-- 1.3.6.1.4.1.10106.3.101291.1.1.327
		htg2000c01v2AudGrpPres4 OBJECT-TYPE
			SYNTAX BitFailN
			MAX-ACCESS read-only
			STATUS current
			DESCRIPTION
				"Group 4 present"
		::= { htg2000c01v2Entry 327 }

		-- 1.3.6.1.4.1.10106.3.101291.1.1.329
		htg2000c01v2AvSeqPhase OBJECT-TYPE
			SYNTAX Uint8
			MAX-ACCESS read-only
			STATUS current
			DESCRIPTION
				"Seconds remaining until next delay measurement sequence starts"
		::= { htg2000c01v2Entry 329 }

		-- 1.3.6.1.4.1.10106.3.456201
		aad2000c01v1 OBJECT IDENTIFIER ::= { albalaProducts 456201 }

		-- 1.3.6.1.4.1.10106.3.456201.1
		aad2000c01v1Table  OBJECT-TYPE
			SYNTAX SEQUENCE OF Aad2000c01v1Entry
			MAX-ACCESS not-accessible
			STATUS current
			DESCRIPTION
				"Module  AAD2000C01V1 Table"
			::= { aad2000c01v1 1 }

		-- 1.3.6.1.4.1.10106.3.456201.1.1
		aad2000c01v1Entry  OBJECT-TYPE
			SYNTAX Aad2000c01v1Entry
			MAX-ACCESS not-accessible
			STATUS current
			DESCRIPTION
				"Module AAD2000C01V1 Entry"
			INDEX { aad2000c01v1Index }
			::= { aad2000c01v1Table 1 }

			Aad2000c01v1Entry ::=
			SEQUENCE {
				aad2000c01v1Index
				ModuleIndex,
				aad2000c01v1Input
				Bit0Dis1Ena,
				aad2000c01v1BckTxEn
				Bit0Dis1Ena,
				aad2000c01v1LedMode
				LedMode,
				aad2000c01v1Vu8dbu
				Vu0Mode,
				aad2000c01v1OvlThrLevel
				LevelDbuD2,
				aad2000c01v1SilThrLevel
				LevelDbuD2,
				aad2000c01v1NoSigTout
				TimeS2,
				aad2000c01v1Silence
				BitFail,
				aad2000c01v1SilenceTrapEnable
				AlarmEnable,
				aad2000c01v1Overload
				BitFail,
				aad2000c01v1OverloadTrapEnable
				AlarmEnable,
				aad2000c01v1VuLevel
				LevelVu2,
				aad2000c01v1PkLevel
				LevelDbuD2,
				aad2000c01v1SerialNo
				SerialNo
			 }

		-- 1.3.6.1.4.1.10106.3.101291.1.1.1
		aad2000c01v1Index OBJECT-TYPE
			SYNTAX ModuleIndex
			MAX-ACCESS read-only
			STATUS current
			DESCRIPTION
				"Index of AAD2000C01V1 Table"
		::= { aad2000c01v1Entry 1 }

		-- 1.3.6.1.4.1.10106.3.101291.1.1.3
		aad2000c01v1Input OBJECT-TYPE
			SYNTAX Bit0Dis1Ena
			MAX-ACCESS read-write
			STATUS current
			DESCRIPTION
				"Allows enabling input from backplane"
		::= { aad2000c01v1Entry 3 }

		-- 1.3.6.1.4.1.10106.3.101291.1.1.5
		aad2000c01v1BckTxEn OBJECT-TYPE
			SYNTAX Bit0Dis1Ena
			MAX-ACCESS read-write
			STATUS current
			DESCRIPTION
				"Allows adding signals on backplane"
		::= { aad2000c01v1Entry 5 }

		-- 1.3.6.1.4.1.10106.3.101291.1.1.7
		aad2000c01v1LedMode OBJECT-TYPE
			SYNTAX LedMode
			MAX-ACCESS read-write
			STATUS current
			DESCRIPTION
				"Allows selecting the led indicator mode"
		::= { aad2000c01v1Entry 7 }

		-- 1.3.6.1.4.1.10106.3.101291.1.1.9
		aad2000c01v1Vu8dbu OBJECT-TYPE
			SYNTAX Vu0Mode
			MAX-ACCESS read-write
			STATUS current
			DESCRIPTION
				"Allows selecting 0 VU level"
		::= { aad2000c01v1Entry 9 }

		-- 1.3.6.1.4.1.10106.3.101291.1.1.11
		aad2000c01v1OvlThrLevel OBJECT-TYPE
			SYNTAX LevelDbuD2
			MAX-ACCESS read-write
			STATUS current
			DESCRIPTION
				"Overload threshold level"
		::= { aad2000c01v1Entry 11 }

		-- 1.3.6.1.4.1.10106.3.101291.1.1.13
		aad2000c01v1SilThrLevel OBJECT-TYPE
			SYNTAX LevelDbuD2
			MAX-ACCESS read-write
			STATUS current
			DESCRIPTION
				"Silence threshold level"
		::= { aad2000c01v1Entry 13 }

		-- 1.3.6.1.4.1.10106.3.101291.1.1.15
		aad2000c01v1NoSigTout OBJECT-TYPE
			SYNTAX TimeS2
			MAX-ACCESS read-write
			STATUS current
			DESCRIPTION
				"Silence timeout"
		::= { aad2000c01v1Entry 15 }

		-- 1.3.6.1.4.1.10106.3.101291.1.1.17
		aad2000c01v1Silence OBJECT-TYPE
			SYNTAX BitFail
			MAX-ACCESS read-only
			STATUS current
			DESCRIPTION
				"Silence fail"
		::= { aad2000c01v1Entry 17 }

		-- 1.3.6.1.4.1.10106.3.101291.1.1.18
		aad2000c01v1SilenceTrapEnable OBJECT-TYPE
			SYNTAX AlarmEnable
			MAX-ACCESS read-write
			STATUS current
			DESCRIPTION
				"Silence fail Trap Enable"
		::= { aad2000c01v1Entry 18 }

		-- 1.3.6.1.4.1.10106.3.101291.1.1.19
		aad2000c01v1Overload OBJECT-TYPE
			SYNTAX BitFail
			MAX-ACCESS read-only
			STATUS current
			DESCRIPTION
				"Overload fail"
		::= { aad2000c01v1Entry 19 }

		-- 1.3.6.1.4.1.10106.3.101291.1.1.20
		aad2000c01v1OverloadTrapEnable OBJECT-TYPE
			SYNTAX AlarmEnable
			MAX-ACCESS read-write
			STATUS current
			DESCRIPTION
				"Overload fail Trap Enable"
		::= { aad2000c01v1Entry 20 }

		-- 1.3.6.1.4.1.10106.3.101291.1.1.21
		aad2000c01v1VuLevel OBJECT-TYPE
			SYNTAX LevelVu2
			MAX-ACCESS read-only
			STATUS current
			DESCRIPTION
				"VU level"
		::= { aad2000c01v1Entry 21 }

		-- 1.3.6.1.4.1.10106.3.101291.1.1.23
		aad2000c01v1PkLevel OBJECT-TYPE
			SYNTAX LevelDbuD2
			MAX-ACCESS read-only
			STATUS current
			DESCRIPTION
				"Peak level"
		::= { aad2000c01v1Entry 23 }

		-- 1.3.6.1.4.1.10106.3.101291.1.1.25
		aad2000c01v1SerialNo OBJECT-TYPE
			SYNTAX SerialNo
			MAX-ACCESS read-only
			STATUS current
			DESCRIPTION
				"Serial number"
		::= { aad2000c01v1Entry 25 }

		-- 1.3.6.1.4.1.10106.3.460201
		aad2000c02v1 OBJECT IDENTIFIER ::= { albalaProducts 460201 }

		-- 1.3.6.1.4.1.10106.3.460201.1
		aad2000c02v1Table  OBJECT-TYPE
			SYNTAX SEQUENCE OF Aad2000c02v1Entry
			MAX-ACCESS not-accessible
			STATUS current
			DESCRIPTION
				"Module  AAD2000C02V1 Table"
			::= { aad2000c02v1 1 }

		-- 1.3.6.1.4.1.10106.3.460201.1.1
		aad2000c02v1Entry  OBJECT-TYPE
			SYNTAX Aad2000c02v1Entry
			MAX-ACCESS not-accessible
			STATUS current
			DESCRIPTION
				"Module AAD2000C02V1 Entry"
			INDEX { aad2000c02v1Index }
			::= { aad2000c02v1Table 1 }

			Aad2000c02v1Entry ::=
			SEQUENCE {
				aad2000c02v1Index
				ModuleIndex,
				aad2000c02v1Input
				Bit0Dis1Ena,
				aad2000c02v1BckTxEn
				Bit0Dis1Ena,
				aad2000c02v1LedMode
				LedMode,
				aad2000c02v1Vu8dbu
				Vu0Mode,
				aad2000c02v1OvlThrLevel
				LevelDbuD2,
				aad2000c02v1SilThrLevel
				LevelDbuD2,
				aad2000c02v1NoSigTout
				TimeS2,
				aad2000c02v1Silence
				BitFail,
				aad2000c02v1SilenceTrapEnable
				AlarmEnable,
				aad2000c02v1Overload
				BitFail,
				aad2000c02v1OverloadTrapEnable
				AlarmEnable,
				aad2000c02v1VuLevel
				LevelVu2,
				aad2000c02v1PkLevel
				LevelDbuD2,
				aad2000c02v1SerialNo
				SerialNo
			 }

		-- 1.3.6.1.4.1.10106.3.101291.1.1.1
		aad2000c02v1Index OBJECT-TYPE
			SYNTAX ModuleIndex
			MAX-ACCESS read-only
			STATUS current
			DESCRIPTION
				"Index of AAD2000C02V1 Table"
		::= { aad2000c02v1Entry 1 }

		-- 1.3.6.1.4.1.10106.3.101291.1.1.3
		aad2000c02v1Input OBJECT-TYPE
			SYNTAX Bit0Dis1Ena
			MAX-ACCESS read-write
			STATUS current
			DESCRIPTION
				"Allows enabling input from backplane"
		::= { aad2000c02v1Entry 3 }

		-- 1.3.6.1.4.1.10106.3.101291.1.1.5
		aad2000c02v1BckTxEn OBJECT-TYPE
			SYNTAX Bit0Dis1Ena
			MAX-ACCESS read-write
			STATUS current
			DESCRIPTION
				"Allows adding signals on backplane"
		::= { aad2000c02v1Entry 5 }

		-- 1.3.6.1.4.1.10106.3.101291.1.1.7
		aad2000c02v1LedMode OBJECT-TYPE
			SYNTAX LedMode
			MAX-ACCESS read-write
			STATUS current
			DESCRIPTION
				"Allows selecting the led indicator mode"
		::= { aad2000c02v1Entry 7 }

		-- 1.3.6.1.4.1.10106.3.101291.1.1.9
		aad2000c02v1Vu8dbu OBJECT-TYPE
			SYNTAX Vu0Mode
			MAX-ACCESS read-write
			STATUS current
			DESCRIPTION
				"Allows selecting 0 VU level"
		::= { aad2000c02v1Entry 9 }

		-- 1.3.6.1.4.1.10106.3.101291.1.1.11
		aad2000c02v1OvlThrLevel OBJECT-TYPE
			SYNTAX LevelDbuD2
			MAX-ACCESS read-write
			STATUS current
			DESCRIPTION
				"Overload threshold level"
		::= { aad2000c02v1Entry 11 }

		-- 1.3.6.1.4.1.10106.3.101291.1.1.13
		aad2000c02v1SilThrLevel OBJECT-TYPE
			SYNTAX LevelDbuD2
			MAX-ACCESS read-write
			STATUS current
			DESCRIPTION
				"Silence threshold level"
		::= { aad2000c02v1Entry 13 }

		-- 1.3.6.1.4.1.10106.3.101291.1.1.15
		aad2000c02v1NoSigTout OBJECT-TYPE
			SYNTAX TimeS2
			MAX-ACCESS read-write
			STATUS current
			DESCRIPTION
				"Silence timeout"
		::= { aad2000c02v1Entry 15 }

		-- 1.3.6.1.4.1.10106.3.101291.1.1.17
		aad2000c02v1Silence OBJECT-TYPE
			SYNTAX BitFail
			MAX-ACCESS read-only
			STATUS current
			DESCRIPTION
				"Silence fail"
		::= { aad2000c02v1Entry 17 }

		-- 1.3.6.1.4.1.10106.3.101291.1.1.18
		aad2000c02v1SilenceTrapEnable OBJECT-TYPE
			SYNTAX AlarmEnable
			MAX-ACCESS read-write
			STATUS current
			DESCRIPTION
				"Silence fail Trap Enable"
		::= { aad2000c02v1Entry 18 }

		-- 1.3.6.1.4.1.10106.3.101291.1.1.19
		aad2000c02v1Overload OBJECT-TYPE
			SYNTAX BitFail
			MAX-ACCESS read-only
			STATUS current
			DESCRIPTION
				"Overload fail"
		::= { aad2000c02v1Entry 19 }

		-- 1.3.6.1.4.1.10106.3.101291.1.1.20
		aad2000c02v1OverloadTrapEnable OBJECT-TYPE
			SYNTAX AlarmEnable
			MAX-ACCESS read-write
			STATUS current
			DESCRIPTION
				"Overload fail Trap Enable"
		::= { aad2000c02v1Entry 20 }

		-- 1.3.6.1.4.1.10106.3.101291.1.1.21
		aad2000c02v1VuLevel OBJECT-TYPE
			SYNTAX LevelVu2
			MAX-ACCESS read-only
			STATUS current
			DESCRIPTION
				"VU level"
		::= { aad2000c02v1Entry 21 }

		-- 1.3.6.1.4.1.10106.3.101291.1.1.23
		aad2000c02v1PkLevel OBJECT-TYPE
			SYNTAX LevelDbuD2
			MAX-ACCESS read-only
			STATUS current
			DESCRIPTION
				"Peak level"
		::= { aad2000c02v1Entry 23 }

		-- 1.3.6.1.4.1.10106.3.101291.1.1.25
		aad2000c02v1SerialNo OBJECT-TYPE
			SYNTAX SerialNo
			MAX-ACCESS read-only
			STATUS current
			DESCRIPTION
				"Serial number"
		::= { aad2000c02v1Entry 25 }

		-- 1.3.6.1.4.1.10106.3.460301
		aad2000c03v1 OBJECT IDENTIFIER ::= { albalaProducts 460301 }

		-- 1.3.6.1.4.1.10106.3.460301.1
		aad2000c03v1Table  OBJECT-TYPE
			SYNTAX SEQUENCE OF Aad2000c03v1Entry
			MAX-ACCESS not-accessible
			STATUS current
			DESCRIPTION
				"Module  AAD2000C03V1 Table"
			::= { aad2000c03v1 1 }

		-- 1.3.6.1.4.1.10106.3.460301.1.1
		aad2000c03v1Entry  OBJECT-TYPE
			SYNTAX Aad2000c03v1Entry
			MAX-ACCESS not-accessible
			STATUS current
			DESCRIPTION
				"Module AAD2000C03V1 Entry"
			INDEX { aad2000c03v1Index }
			::= { aad2000c03v1Table 1 }

			Aad2000c03v1Entry ::=
			SEQUENCE {
				aad2000c03v1Index
				ModuleIndex,
				aad2000c03v1Input
				Bit0Dis1Ena,
				aad2000c03v1BckTxEn
				Bit0Dis1Ena,
				aad2000c03v1LedMode
				LedMode,
				aad2000c03v1Vu8dbu
				Vu0Mode,
				aad2000c03v1OvlThrLevel
				LevelDbuD2,
				aad2000c03v1SilThrLevel
				LevelDbuD2,
				aad2000c03v1NoSigTout
				TimeS2,
				aad2000c03v1Silence
				BitFail,
				aad2000c03v1SilenceTrapEnable
				AlarmEnable,
				aad2000c03v1Overload
				BitFail,
				aad2000c03v1OverloadTrapEnable
				AlarmEnable,
				aad2000c03v1VuLevel
				LevelVu2,
				aad2000c03v1PkLevel
				LevelDbuD2,
				aad2000c03v1SerialNo
				SerialNo
			 }

		-- 1.3.6.1.4.1.10106.3.101291.1.1.1
		aad2000c03v1Index OBJECT-TYPE
			SYNTAX ModuleIndex
			MAX-ACCESS read-only
			STATUS current
			DESCRIPTION
				"Index of AAD2000C03V1 Table"
		::= { aad2000c03v1Entry 1 }

		-- 1.3.6.1.4.1.10106.3.101291.1.1.3
		aad2000c03v1Input OBJECT-TYPE
			SYNTAX Bit0Dis1Ena
			MAX-ACCESS read-write
			STATUS current
			DESCRIPTION
				"Allows enabling input from backplane"
		::= { aad2000c03v1Entry 3 }

		-- 1.3.6.1.4.1.10106.3.101291.1.1.5
		aad2000c03v1BckTxEn OBJECT-TYPE
			SYNTAX Bit0Dis1Ena
			MAX-ACCESS read-write
			STATUS current
			DESCRIPTION
				"Allows adding signals on backplane"
		::= { aad2000c03v1Entry 5 }

		-- 1.3.6.1.4.1.10106.3.101291.1.1.7
		aad2000c03v1LedMode OBJECT-TYPE
			SYNTAX LedMode
			MAX-ACCESS read-write
			STATUS current
			DESCRIPTION
				"Allows selecting the led indicator mode"
		::= { aad2000c03v1Entry 7 }

		-- 1.3.6.1.4.1.10106.3.101291.1.1.9
		aad2000c03v1Vu8dbu OBJECT-TYPE
			SYNTAX Vu0Mode
			MAX-ACCESS read-write
			STATUS current
			DESCRIPTION
				"Allows selecting 0 VU level"
		::= { aad2000c03v1Entry 9 }

		-- 1.3.6.1.4.1.10106.3.101291.1.1.11
		aad2000c03v1OvlThrLevel OBJECT-TYPE
			SYNTAX LevelDbuD2
			MAX-ACCESS read-write
			STATUS current
			DESCRIPTION
				"Overload threshold level"
		::= { aad2000c03v1Entry 11 }

		-- 1.3.6.1.4.1.10106.3.101291.1.1.13
		aad2000c03v1SilThrLevel OBJECT-TYPE
			SYNTAX LevelDbuD2
			MAX-ACCESS read-write
			STATUS current
			DESCRIPTION
				"Silence threshold level"
		::= { aad2000c03v1Entry 13 }

		-- 1.3.6.1.4.1.10106.3.101291.1.1.15
		aad2000c03v1NoSigTout OBJECT-TYPE
			SYNTAX TimeS2
			MAX-ACCESS read-write
			STATUS current
			DESCRIPTION
				"Silence timeout"
		::= { aad2000c03v1Entry 15 }

		-- 1.3.6.1.4.1.10106.3.101291.1.1.17
		aad2000c03v1Silence OBJECT-TYPE
			SYNTAX BitFail
			MAX-ACCESS read-only
			STATUS current
			DESCRIPTION
				"Silence fail"
		::= { aad2000c03v1Entry 17 }

		-- 1.3.6.1.4.1.10106.3.101291.1.1.18
		aad2000c03v1SilenceTrapEnable OBJECT-TYPE
			SYNTAX AlarmEnable
			MAX-ACCESS read-write
			STATUS current
			DESCRIPTION
				"Silence fail Trap Enable"
		::= { aad2000c03v1Entry 18 }

		-- 1.3.6.1.4.1.10106.3.101291.1.1.19
		aad2000c03v1Overload OBJECT-TYPE
			SYNTAX BitFail
			MAX-ACCESS read-only
			STATUS current
			DESCRIPTION
				"Overload fail"
		::= { aad2000c03v1Entry 19 }

		-- 1.3.6.1.4.1.10106.3.101291.1.1.20
		aad2000c03v1OverloadTrapEnable OBJECT-TYPE
			SYNTAX AlarmEnable
			MAX-ACCESS read-write
			STATUS current
			DESCRIPTION
				"Overload fail Trap Enable"
		::= { aad2000c03v1Entry 20 }

		-- 1.3.6.1.4.1.10106.3.101291.1.1.21
		aad2000c03v1VuLevel OBJECT-TYPE
			SYNTAX LevelVu2
			MAX-ACCESS read-only
			STATUS current
			DESCRIPTION
				"VU level"
		::= { aad2000c03v1Entry 21 }

		-- 1.3.6.1.4.1.10106.3.101291.1.1.23
		aad2000c03v1PkLevel OBJECT-TYPE
			SYNTAX LevelDbuD2
			MAX-ACCESS read-only
			STATUS current
			DESCRIPTION
				"Peak level"
		::= { aad2000c03v1Entry 23 }

		-- 1.3.6.1.4.1.10106.3.101291.1.1.25
		aad2000c03v1SerialNo OBJECT-TYPE
			SYNTAX SerialNo
			MAX-ACCESS read-only
			STATUS current
			DESCRIPTION
				"Serial number"
		::= { aad2000c03v1Entry 25 }

		-- 1.3.6.1.4.1.10106.3.460401
		aad2000c04v1 OBJECT IDENTIFIER ::= { albalaProducts 460401 }

		-- 1.3.6.1.4.1.10106.3.460401.1
		aad2000c04v1Table  OBJECT-TYPE
			SYNTAX SEQUENCE OF Aad2000c04v1Entry
			MAX-ACCESS not-accessible
			STATUS current
			DESCRIPTION
				"Module  AAD2000C04V1 Table"
			::= { aad2000c04v1 1 }

		-- 1.3.6.1.4.1.10106.3.460401.1.1
		aad2000c04v1Entry  OBJECT-TYPE
			SYNTAX Aad2000c04v1Entry
			MAX-ACCESS not-accessible
			STATUS current
			DESCRIPTION
				"Module AAD2000C04V1 Entry"
			INDEX { aad2000c04v1Index }
			::= { aad2000c04v1Table 1 }

			Aad2000c04v1Entry ::=
			SEQUENCE {
				aad2000c04v1Index
				ModuleIndex,
				aad2000c04v1Input
				Bit0Dis1Ena,
				aad2000c04v1BckTxEn
				Bit0Dis1Ena,
				aad2000c04v1LedMode
				LedMode,
				aad2000c04v1Vu8dbu
				Vu0Mode,
				aad2000c04v1OvlThrLevel
				LevelDbuD2,
				aad2000c04v1SilThrLevel
				LevelDbuD2,
				aad2000c04v1NoSigTout
				TimeS2,
				aad2000c04v1Silence
				BitFail,
				aad2000c04v1SilenceTrapEnable
				AlarmEnable,
				aad2000c04v1Overload
				BitFail,
				aad2000c04v1OverloadTrapEnable
				AlarmEnable,
				aad2000c04v1VuLevel
				LevelVu2,
				aad2000c04v1PkLevel
				LevelDbuD2,
				aad2000c04v1SerialNo
				SerialNo
			 }

		-- 1.3.6.1.4.1.10106.3.101291.1.1.1
		aad2000c04v1Index OBJECT-TYPE
			SYNTAX ModuleIndex
			MAX-ACCESS read-only
			STATUS current
			DESCRIPTION
				"Index of AAD2000C04V1 Table"
		::= { aad2000c04v1Entry 1 }

		-- 1.3.6.1.4.1.10106.3.101291.1.1.3
		aad2000c04v1Input OBJECT-TYPE
			SYNTAX Bit0Dis1Ena
			MAX-ACCESS read-write
			STATUS current
			DESCRIPTION
				"Allows enabling input from backplane"
		::= { aad2000c04v1Entry 3 }

		-- 1.3.6.1.4.1.10106.3.101291.1.1.5
		aad2000c04v1BckTxEn OBJECT-TYPE
			SYNTAX Bit0Dis1Ena
			MAX-ACCESS read-write
			STATUS current
			DESCRIPTION
				"Allows adding signals on backplane"
		::= { aad2000c04v1Entry 5 }

		-- 1.3.6.1.4.1.10106.3.101291.1.1.7
		aad2000c04v1LedMode OBJECT-TYPE
			SYNTAX LedMode
			MAX-ACCESS read-write
			STATUS current
			DESCRIPTION
				"Allows selecting the led indicator mode"
		::= { aad2000c04v1Entry 7 }

		-- 1.3.6.1.4.1.10106.3.101291.1.1.9
		aad2000c04v1Vu8dbu OBJECT-TYPE
			SYNTAX Vu0Mode
			MAX-ACCESS read-write
			STATUS current
			DESCRIPTION
				"Allows selecting 0 VU level"
		::= { aad2000c04v1Entry 9 }

		-- 1.3.6.1.4.1.10106.3.101291.1.1.11
		aad2000c04v1OvlThrLevel OBJECT-TYPE
			SYNTAX LevelDbuD2
			MAX-ACCESS read-write
			STATUS current
			DESCRIPTION
				"Overload threshold level"
		::= { aad2000c04v1Entry 11 }

		-- 1.3.6.1.4.1.10106.3.101291.1.1.13
		aad2000c04v1SilThrLevel OBJECT-TYPE
			SYNTAX LevelDbuD2
			MAX-ACCESS read-write
			STATUS current
			DESCRIPTION
				"Silence threshold level"
		::= { aad2000c04v1Entry 13 }

		-- 1.3.6.1.4.1.10106.3.101291.1.1.15
		aad2000c04v1NoSigTout OBJECT-TYPE
			SYNTAX TimeS2
			MAX-ACCESS read-write
			STATUS current
			DESCRIPTION
				"Silence timeout"
		::= { aad2000c04v1Entry 15 }

		-- 1.3.6.1.4.1.10106.3.101291.1.1.17
		aad2000c04v1Silence OBJECT-TYPE
			SYNTAX BitFail
			MAX-ACCESS read-only
			STATUS current
			DESCRIPTION
				"Silence fail"
		::= { aad2000c04v1Entry 17 }

		-- 1.3.6.1.4.1.10106.3.101291.1.1.18
		aad2000c04v1SilenceTrapEnable OBJECT-TYPE
			SYNTAX AlarmEnable
			MAX-ACCESS read-write
			STATUS current
			DESCRIPTION
				"Silence fail Trap Enable"
		::= { aad2000c04v1Entry 18 }

		-- 1.3.6.1.4.1.10106.3.101291.1.1.19
		aad2000c04v1Overload OBJECT-TYPE
			SYNTAX BitFail
			MAX-ACCESS read-only
			STATUS current
			DESCRIPTION
				"Overload fail"
		::= { aad2000c04v1Entry 19 }

		-- 1.3.6.1.4.1.10106.3.101291.1.1.20
		aad2000c04v1OverloadTrapEnable OBJECT-TYPE
			SYNTAX AlarmEnable
			MAX-ACCESS read-write
			STATUS current
			DESCRIPTION
				"Overload fail Trap Enable"
		::= { aad2000c04v1Entry 20 }

		-- 1.3.6.1.4.1.10106.3.101291.1.1.21
		aad2000c04v1VuLevel OBJECT-TYPE
			SYNTAX LevelVu2
			MAX-ACCESS read-only
			STATUS current
			DESCRIPTION
				"VU level"
		::= { aad2000c04v1Entry 21 }

		-- 1.3.6.1.4.1.10106.3.101291.1.1.23
		aad2000c04v1PkLevel OBJECT-TYPE
			SYNTAX LevelDbuD2
			MAX-ACCESS read-only
			STATUS current
			DESCRIPTION
				"Peak level"
		::= { aad2000c04v1Entry 23 }

		-- 1.3.6.1.4.1.10106.3.101291.1.1.25
		aad2000c04v1SerialNo OBJECT-TYPE
			SYNTAX SerialNo
			MAX-ACCESS read-only
			STATUS current
			DESCRIPTION
				"Serial number"
		::= { aad2000c04v1Entry 25 }

		-- 1.3.6.1.4.1.10106.3.461001
		ipa2000c01v1 OBJECT IDENTIFIER ::= { albalaProducts 461001 }

		-- 1.3.6.1.4.1.10106.3.461001.1
		ipa2000c01v1Table  OBJECT-TYPE
			SYNTAX SEQUENCE OF Ipa2000c01v1Entry
			MAX-ACCESS not-accessible
			STATUS current
			DESCRIPTION
				"Module  IPA2000C01V1 Table"
			::= { ipa2000c01v1 1 }

		-- 1.3.6.1.4.1.10106.3.461001.1.1
		ipa2000c01v1Entry  OBJECT-TYPE
			SYNTAX Ipa2000c01v1Entry
			MAX-ACCESS not-accessible
			STATUS current
			DESCRIPTION
				"Module IPA2000C01V1 Entry"
			INDEX { ipa2000c01v1Index }
			::= { ipa2000c01v1Table 1 }

			Ipa2000c01v1Entry ::=
			SEQUENCE {
				ipa2000c01v1Index
				ModuleIndex,
				ipa2000c01v1ActivePreset
				Preset16Active,
				ipa2000c01v1LoadPreset
				Preset16Load,
				ipa2000c01v1SavePreset
				Preset16Save,
				ipa2000c01v1InputStChRst
				Bit0No1Yes,
				ipa2000c01v1InputChRst
				Bit0No1Yes,
				ipa2000c01v1StatReset
				Bit0No1Yes,
				ipa2000c01v1StatMode
				Bit01s1Total,
				ipa2000c01v1IgmpVersion
				Bit0No1Yes,
				ipa2000c01v1Input
				ChgOverIn2B,
				ipa2000c01v1InputTrapEnable
				AlarmEnable,
				ipa2000c01v1SwMode
				ChgOverMode2,
				ipa2000c01v1SwModeTrapEnable
				AlarmEnable,
				ipa2000c01v1Ch1Prior
				Uint2,
				ipa2000c01v1Ch1PriorTrapEnable
				AlarmEnable,
				ipa2000c01v1Ch2Prior
				Uint2,
				ipa2000c01v1Ch2PriorTrapEnable
				AlarmEnable,
				ipa2000c01v1MaxTimeOut
				TimeX1Ms1,
				ipa2000c01v1EnSeamNondvbt
				Bit0No1Yes,
				ipa2000c01v1NarrowPllBw
				Bit0No1Yes,
				ipa2000c01v1DvbTMode
				Bit0No1Yes,
				ipa2000c01v1DvbTModeTrapEnable
				AlarmEnable,
				ipa2000c01v1NullPckRtp
				Bit0No1Yes,
				ipa2000c01v1TxAsi1En
				InputOutput,
				ipa2000c01v1TxAsi2En
				InputOutput,
				ipa2000c01v1TxAsi1AuxEn
				InputOutputAux,
				ipa2000c01v1TxAsi2AuxEn
				InputOutputAux,
				ipa2000c01v1RxIp1Inter
				IpInterface,
				ipa2000c01v1RxIp2Inter
				IpInterface,
				ipa2000c01v1TxIp1Inter
				IpInterface,
				ipa2000c01v1TxIp2Inter
				IpInterface,
				ipa2000c01v1TxIp1OutSel
				IpaOutSel,
				ipa2000c01v1TxIp2OutSel
				IpaOutSel,
				ipa2000c01v1EthMode1
				EthMode2000,
				ipa2000c01v1EthMode2
				EthMode2000,
				ipa2000c01v1Ch1Selection
				IpaChSelection,
				ipa2000c01v1Ch1SelectionTrapEnable
				AlarmEnable,
				ipa2000c01v1Ch2Selection
				IpaChSelection,
				ipa2000c01v1Ch2SelectionTrapEnable
				AlarmEnable,
				ipa2000c01v1TsSyncLossEn
				Bit0No1Yes,
				ipa2000c01v1SyncByErrorEn
				Bit0No1Yes,
				ipa2000c01v1PatErrorEn
				Bit0No1Yes,
				ipa2000c01v1CcErrorEn
				Bit0No1Yes,
				ipa2000c01v1PmtErrorEn
				Bit0No1Yes,
				ipa2000c01v1PidErrorEn
				Bit0No1Yes,
				ipa2000c01v1PidErrorTime
				TimeX1Ms1,
				ipa2000c01v1OutDelay
				DelayX100Ns,
				ipa2000c01v1OutDelayTrapEnable
				AlarmEnable,
				ipa2000c01v1PacketDelay
				DelayPacket1,
				ipa2000c01v1PacketDelayTrapEnable
				AlarmEnable,
				ipa2000c01v1Str1Ena
				Bit0No1Yes,
				ipa2000c01v1Str1MulticEna
				IpaTxMode,
				ipa2000c01v1Str1FecEna
				Bit0No1Yes,
				ipa2000c01v1Str1UipDAdd3
				Uint8,
				ipa2000c01v1Str1UipDAdd2
				Uint8,
				ipa2000c01v1Str1UipDAdd1
				Uint8,
				ipa2000c01v1Str1UipDAdd0
				Uint8,
				ipa2000c01v1Str1MipDAdd3
				Uint8,
				ipa2000c01v1Str1MipDAdd2
				Uint8,
				ipa2000c01v1Str1MipDAdd1
				Uint8,
				ipa2000c01v1Str1MipDAdd0
				Uint8,
				ipa2000c01v1Str1IgmFAdd3
				Uint8,
				ipa2000c01v1Str1IgmFAdd2
				Uint8,
				ipa2000c01v1Str1IgmFAdd1
				Uint8,
				ipa2000c01v1Str1IgmFAdd0
				Uint8,
				ipa2000c01v1Str1DPort
				Uint16,
				ipa2000c01v1RxIp1SrMsk
				Uint8,
				ipa2000c01v1RxIp1SrMsk2
				Uint8,
				ipa2000c01v1RxIp1SrMsk1
				Uint8,
				ipa2000c01v1RxIp1SrMsk0
				Uint8,
				ipa2000c01v1Str2Ena
				Bit0No1Yes,
				ipa2000c01v1Str2MulticEna
				IpaTxMode,
				ipa2000c01v1Str2FecEna
				Bit0No1Yes,
				ipa2000c01v1Str2UipDAdd3
				Uint8,
				ipa2000c01v1Str2UipDAdd2
				Uint8,
				ipa2000c01v1Str2UipDAdd1
				Uint8,
				ipa2000c01v1Str2UipDAdd0
				Uint8,
				ipa2000c01v1Str2MipDAdd3
				Uint8,
				ipa2000c01v1Str2MipDAdd2
				Uint8,
				ipa2000c01v1Str2MipDAdd1
				Uint8,
				ipa2000c01v1Str2MipDAdd0
				Uint8,
				ipa2000c01v1Str2IgmFAdd3
				Uint8,
				ipa2000c01v1Str2IgmFAdd2
				Uint8,
				ipa2000c01v1Str2IgmFAdd1
				Uint8,
				ipa2000c01v1Str2IgmFAdd0
				Uint8,
				ipa2000c01v1Str2DPort
				Uint16,
				ipa2000c01v1RxIp2SrMsk
				Uint8,
				ipa2000c01v1RxIp2SrMsk1
				Uint8,
				ipa2000c01v1RxIp2SrMsk2
				Uint8,
				ipa2000c01v1RxIp2SrMsk3
				Uint8,
				ipa2000c01v1Tx1UniEna
				Bit0No1Yes,
				ipa2000c01v1Tx1MultiEna
				IpaTxMode,
				ipa2000c01v1Tx1MipAdd3
				Uint8,
				ipa2000c01v1Tx1MipAdd2
				Uint8,
				ipa2000c01v1Tx1MipAdd1
				Uint8,
				ipa2000c01v1Tx1MipAdd0
				Uint8,
				ipa2000c01v1Tx1UipAdd3
				Uint8,
				ipa2000c01v1Tx1UipAdd2
				Uint8,
				ipa2000c01v1Tx1UipAdd1
				Uint8,
				ipa2000c01v1Tx1UipAdd0
				Uint8,
				ipa2000c01v1Tx1SPort
				Uint16,
				ipa2000c01v1Tx1DPort
				Uint16,
				ipa2000c01v1Tx1LParam
				Uint5,
				ipa2000c01v1Tx1FecMode
				FecMode,
				ipa2000c01v1Tx1DParam
				Uint5,
				ipa2000c01v1Tx1TspkInIppk
				Uint3,
				ipa2000c01v1Tx1RowDelay
				Uint5,
				ipa2000c01v1Tx1ColDelay
				Uint8,
				ipa2000c01v1TxIp1SrAdd3
				Uint8,
				ipa2000c01v1TxIp1SrAdd2
				Uint8,
				ipa2000c01v1TxIp1SrAdd1
				Uint8,
				ipa2000c01v1TxIp1SrAdd0
				Uint8,
				ipa2000c01v1TxIp1SrMsk0
				Uint8,
				ipa2000c01v1TxIp1SrMsk1
				Uint8,
				ipa2000c01v1TxIp1SrMsk2
				Uint8,
				ipa2000c01v1TxIp1SrMsk3
				Uint8,
				ipa2000c01v1Tx2UniEna
				Bit0No1Yes,
				ipa2000c01v1Tx2MultiEna
				IpaTxMode,
				ipa2000c01v1Tx2MipAdd3
				Uint8,
				ipa2000c01v1Tx2MipAdd2
				Uint8,
				ipa2000c01v1Tx2MipAdd1
				Uint8,
				ipa2000c01v1Tx2MipAdd0
				Uint8,
				ipa2000c01v1Tx2UipAdd3
				Uint8,
				ipa2000c01v1Tx2UipAdd2
				Uint8,
				ipa2000c01v1Tx2UipAdd1
				Uint8,
				ipa2000c01v1Tx2UipAdd0
				Uint8,
				ipa2000c01v1Tx2SPort
				Uint16,
				ipa2000c01v1Tx2DPort
				Uint16,
				ipa2000c01v1Tx2LParam
				Uint5,
				ipa2000c01v1Tx2FecMode
				FecMode,
				ipa2000c01v1Tx2DParam
				Uint5,
				ipa2000c01v1Tx2TspkInIppk
				Uint3,
				ipa2000c01v1Tx2RowDelay
				Uint5,
				ipa2000c01v1Tx2ColDelay
				Uint8,
				ipa2000c01v1TxIp2SrAdd3
				Uint8,
				ipa2000c01v1TxIp2SrAdd2
				Uint8,
				ipa2000c01v1TxIp2SrAdd1
				Uint8,
				ipa2000c01v1TxIp2SrAdd0
				Uint8,
				ipa2000c01v1TxIp2SrMsk0
				Uint8,
				ipa2000c01v1TxIp2SrMsk1
				Uint8,
				ipa2000c01v1TxIp2SrMsk2
				Uint8,
				ipa2000c01v1TxIp2SrMsk3
				Uint8,
				ipa2000c01v1Rx1IpRxAdd3
				Uint8,
				ipa2000c01v1Rx1IpRxAdd2
				Uint8,
				ipa2000c01v1Rx1IpRxAdd1
				Uint8,
				ipa2000c01v1Rx1IpRxAdd0
				Uint8,
				ipa2000c01v1Rx1IpRxPort
				Uint16,
				ipa2000c01v1Rx1LParam
				Uint5,
				ipa2000c01v1Rx1FecMode
				FecMode,
				ipa2000c01v1Rx1PacketSize
				Bit02041188,
				ipa2000c01v1Rx1DParam
				Uint5,
				ipa2000c01v1Rx1TsPcks
				Uint3,
				ipa2000c01v1Rx1PacketRate
				PacketRate,
				ipa2000c01v1Rx1FecRate
				PacketRate,
				ipa2000c01v1Rx1TimeRst
				TimeS4,
				ipa2000c01v1Rx1LostIpPck
				Uint16,
				ipa2000c01v1Rx1RecIpPck
				Uint16,
				ipa2000c01v1Rx1OutOrdPck
				Uint16,
				ipa2000c01v1Rx1BufferStat
				Rate1,
				ipa2000c01v1Rx2IpRxAdd3
				Uint8,
				ipa2000c01v1Rx2IpRxAdd2
				Uint8,
				ipa2000c01v1Rx2IpRxAdd1
				Uint8,
				ipa2000c01v1Rx2IpRxAdd0
				Uint8,
				ipa2000c01v1Rx2IpRxPort
				Uint16,
				ipa2000c01v1Rx2LParam
				Uint5,
				ipa2000c01v1Rx2FecMode
				FecMode,
				ipa2000c01v1Rx2PacketSize
				Bit02041188,
				ipa2000c01v1Rx2DParam
				Uint5,
				ipa2000c01v1Rx2TsPcks
				Uint3,
				ipa2000c01v1Rx2PacketRate
				PacketRate,
				ipa2000c01v1Rx2FecRate
				PacketRate,
				ipa2000c01v1Rx2TimeRst
				TimeS4,
				ipa2000c01v1Rx2LostIpPck
				Uint16,
				ipa2000c01v1Rx2RecIpPck
				Uint16,
				ipa2000c01v1Rx2OutOrdPck
				Uint16,
				ipa2000c01v1Rx2BufferStat
				Rate1,
				ipa2000c01v1LocalIpAdd3
				Uint8,
				ipa2000c01v1LocalIpAdd2
				Uint8,
				ipa2000c01v1LocalIpAdd1
				Uint8,
				ipa2000c01v1LocalIpAdd0
				Uint8,
				ipa2000c01v1LocalIpMask3
				Uint8,
				ipa2000c01v1LocalIpMask2
				Uint8,
				ipa2000c01v1LocalIpMask1
				Uint8,
				ipa2000c01v1LocalIpMask0
				Uint8,
				ipa2000c01v1LocalIp2Add3
				Uint8,
				ipa2000c01v1LocalIp2Add2
				Uint8,
				ipa2000c01v1LocalIp2Add1
				Uint8,
				ipa2000c01v1LocalIp2Add0
				Uint8,
				ipa2000c01v1LocalIp2Msk3
				Uint8,
				ipa2000c01v1LocalIp2Msk2
				Uint8,
				ipa2000c01v1LocalIp2Msk1
				Uint8,
				ipa2000c01v1LocalIp2Msk0
				Uint8,
				ipa2000c01v1LocalIpGway3
				Uint8,
				ipa2000c01v1LocalIpGway2
				Uint8,
				ipa2000c01v1LocalIpGway1
				Uint8,
				ipa2000c01v1LocalIpGway0
				Uint8,
				ipa2000c01v1SysError
				SysError0,
				ipa2000c01v1Link1
				Ipa2EtherStat,
				ipa2000c01v1Link1TrapEnable
				AlarmEnable,
				ipa2000c01v1System1
				Ipa2EtherSys,
				ipa2000c01v1System1TrapEnable
				AlarmEnable,
				ipa2000c01v1Link2
				Ipa2EtherStat,
				ipa2000c01v1Link2TrapEnable
				AlarmEnable,
				ipa2000c01v1System2
				Ipa2EtherSys,
				ipa2000c01v1System2TrapEnable
				AlarmEnable,
				ipa2000c01v11ppsFail
				BitFail,
				ipa2000c01v11ppsFailTrapEnable
				AlarmEnable,
				ipa2000c01v113mhzFail
				BitFail,
				ipa2000c01v113mhzFailTrapEnable
				AlarmEnable,
				ipa2000c01v1OutputFail
				BitFail,
				ipa2000c01v1OutputFailTrapEnable
				AlarmEnable,
				ipa2000c01v1InputStChange
				BitFail,
				ipa2000c01v1InputChange
				BitFail,
				ipa2000c01v1SyncLossErr1
				BitFail,
				ipa2000c01v1SyncLossErr1TrapEnable
				AlarmEnable,
				ipa2000c01v1SyncByteErr1
				BitFail,
				ipa2000c01v1SyncByteErr1TrapEnable
				AlarmEnable,
				ipa2000c01v1PatError1
				BitFail,
				ipa2000c01v1PatError1TrapEnable
				AlarmEnable,
				ipa2000c01v1CcError1
				BitFail,
				ipa2000c01v1CcError1TrapEnable
				AlarmEnable,
				ipa2000c01v1PmtError1
				BitFail,
				ipa2000c01v1PmtError1TrapEnable
				AlarmEnable,
				ipa2000c01v1PidError1
				BitFail,
				ipa2000c01v1PidError1TrapEnable
				AlarmEnable,
				ipa2000c01v1MipError1
				BitFail,
				ipa2000c01v1MipError1TrapEnable
				AlarmEnable,
				ipa2000c01v1GlobalError1
				BitFail,
				ipa2000c01v1GlobalError1TrapEnable
				AlarmEnable,
				ipa2000c01v1SyncLossErr2
				BitFail,
				ipa2000c01v1SyncLossErr2TrapEnable
				AlarmEnable,
				ipa2000c01v1SyncByteErr2
				BitFail,
				ipa2000c01v1SyncByteErr2TrapEnable
				AlarmEnable,
				ipa2000c01v1PatError2
				BitFail,
				ipa2000c01v1PatError2TrapEnable
				AlarmEnable,
				ipa2000c01v1CcError2
				BitFail,
				ipa2000c01v1CcError2TrapEnable
				AlarmEnable,
				ipa2000c01v1PmtError2
				BitFail,
				ipa2000c01v1PmtError2TrapEnable
				AlarmEnable,
				ipa2000c01v1PidError2
				BitFail,
				ipa2000c01v1PidError2TrapEnable
				AlarmEnable,
				ipa2000c01v1MipError2
				BitFail,
				ipa2000c01v1MipError2TrapEnable
				AlarmEnable,
				ipa2000c01v1GlobalError2
				BitFail,
				ipa2000c01v1GlobalError2TrapEnable
				AlarmEnable,
				ipa2000c01v1Ch1DelWar
				BitFail,
				ipa2000c01v1Ch1DelWarTrapEnable
				AlarmEnable,
				ipa2000c01v1Ch2DelWar
				BitFail,
				ipa2000c01v1Ch2DelWarTrapEnable
				AlarmEnable,
				ipa2000c01v1GlobalSeam
				Bit0Sea1Nse,
				ipa2000c01v1GlobalSeamTrapEnable
				AlarmEnable,
				ipa2000c01v1Channel1Delay
				DelayX1004bNs,
				ipa2000c01v1Channel2Delay
				DelayX1004bNs,
				ipa2000c01v1ArpValid1
				BitFailN,
				ipa2000c01v1IcmpError1
				BitFail,
				ipa2000c01v1ArpValid2
				BitFailN,
				ipa2000c01v1IcmpError2
				BitFail,
				ipa2000c01v1SerialNo
				SerialNo,
				ipa2000c01v1SpeedForce1
				Bit0Ann1For,
				ipa2000c01v1SpeedForce2
				Bit0Ann1For,
				ipa2000c01v1BadCrcPck1
				Uint16,
				ipa2000c01v1BadCrcPck2
				Uint16,
				ipa2000c01v1InpFailMode
				Bit0No1Yes,
				ipa2000c01v1PatErrorTime
				TimeX1Ms1,
				ipa2000c01v1PmtErrorTime
				TimeX1Ms1,
				ipa2000c01v1IpRedTx13
				Uint8,
				ipa2000c01v1IpRedTx12
				Uint8,
				ipa2000c01v1IpRedTx11
				Uint8,
				ipa2000c01v1IpRedTx10
				Uint8,
				ipa2000c01v1IpRedTx23
				Uint8,
				ipa2000c01v1IpRedTx22
				Uint8,
				ipa2000c01v1IpRedTx21
				Uint8,
				ipa2000c01v1IpRedTx20
				Uint8,
				ipa2000c01v1TxIpSrcAvai1
				BitFailN,
				ipa2000c01v1TxIpSrcAvai2
				BitFailN,
				ipa2000c01v1Channel1Pck
				PacketNum,
				ipa2000c01v1Channel2Pck
				PacketNum,
				ipa2000c01v1RouterIp13
				Uint8,
				ipa2000c01v1RouterIp12
				Uint8,
				ipa2000c01v1RouterIp11
				Uint8,
				ipa2000c01v1RouterIp10
				Uint8,
				ipa2000c01v1RouterIp23
				Uint8,
				ipa2000c01v1RouterIp22
				Uint8,
				ipa2000c01v1RouterIp21
				Uint8,
				ipa2000c01v1RouterIp20
				Uint8
			 }

		-- 1.3.6.1.4.1.10106.3.101291.1.1.1
		ipa2000c01v1Index OBJECT-TYPE
			SYNTAX ModuleIndex
			MAX-ACCESS read-only
			STATUS current
			DESCRIPTION
				"Index of IPA2000C01V1 Table"
		::= { ipa2000c01v1Entry 1 }

		-- 1.3.6.1.4.1.10106.3.101291.1.1.3
		ipa2000c01v1ActivePreset OBJECT-TYPE
			SYNTAX Preset16Active
			MAX-ACCESS read-only
			STATUS current
			DESCRIPTION
				"Shows the active preset"
		::= { ipa2000c01v1Entry 3 }

		-- 1.3.6.1.4.1.10106.3.101291.1.1.5
		ipa2000c01v1LoadPreset OBJECT-TYPE
			SYNTAX Preset16Load
			MAX-ACCESS read-write
			STATUS current
			DESCRIPTION
				"Allows loading a preset"
		::= { ipa2000c01v1Entry 5 }

		-- 1.3.6.1.4.1.10106.3.101291.1.1.7
		ipa2000c01v1SavePreset OBJECT-TYPE
			SYNTAX Preset16Save
			MAX-ACCESS read-write
			STATUS current
			DESCRIPTION
				"Allows saving a preset"
		::= { ipa2000c01v1Entry 7 }

		-- 1.3.6.1.4.1.10106.3.101291.1.1.9
		ipa2000c01v1InputStChRst OBJECT-TYPE
			SYNTAX Bit0No1Yes
			MAX-ACCESS read-write
			STATUS current
			DESCRIPTION
				"Resets a change input status indication"
		::= { ipa2000c01v1Entry 9 }

		-- 1.3.6.1.4.1.10106.3.101291.1.1.11
		ipa2000c01v1InputChRst OBJECT-TYPE
			SYNTAX Bit0No1Yes
			MAX-ACCESS read-write
			STATUS current
			DESCRIPTION
				"Resets a switching between inputs indication"
		::= { ipa2000c01v1Entry 11 }

		-- 1.3.6.1.4.1.10106.3.101291.1.1.13
		ipa2000c01v1StatReset OBJECT-TYPE
			SYNTAX Bit0No1Yes
			MAX-ACCESS read-write
			STATUS current
			DESCRIPTION
				"Allows reseting the statistics measurements"
		::= { ipa2000c01v1Entry 13 }

		-- 1.3.6.1.4.1.10106.3.101291.1.1.15
		ipa2000c01v1StatMode OBJECT-TYPE
			SYNTAX Bit01s1Total
			MAX-ACCESS read-write
			STATUS current
			DESCRIPTION
				"Allows selecting the statistics mode"
		::= { ipa2000c01v1Entry 15 }

		-- 1.3.6.1.4.1.10106.3.101291.1.1.17
		ipa2000c01v1IgmpVersion OBJECT-TYPE
			SYNTAX Bit0No1Yes
			MAX-ACCESS read-write
			STATUS current
			DESCRIPTION
				"Allows selecting the IGMP version.  When enabled the module IGMP response uses always version 2"
		::= { ipa2000c01v1Entry 17 }

		-- 1.3.6.1.4.1.10106.3.101291.1.1.19
		ipa2000c01v1Input OBJECT-TYPE
			SYNTAX ChgOverIn2B
			MAX-ACCESS read-write
			STATUS current
			DESCRIPTION
				"Selected input"
		::= { ipa2000c01v1Entry 19 }

		-- 1.3.6.1.4.1.10106.3.101291.1.1.20
		ipa2000c01v1InputTrapEnable OBJECT-TYPE
			SYNTAX AlarmEnable
			MAX-ACCESS read-write
			STATUS current
			DESCRIPTION
				"Selected input Trap Enable"
		::= { ipa2000c01v1Entry 20 }

		-- 1.3.6.1.4.1.10106.3.101291.1.1.21
		ipa2000c01v1SwMode OBJECT-TYPE
			SYNTAX ChgOverMode2
			MAX-ACCESS read-write
			STATUS current
			DESCRIPTION
				"Allows selecting the switching mode"
		::= { ipa2000c01v1Entry 21 }

		-- 1.3.6.1.4.1.10106.3.101291.1.1.22
		ipa2000c01v1SwModeTrapEnable OBJECT-TYPE
			SYNTAX AlarmEnable
			MAX-ACCESS read-write
			STATUS current
			DESCRIPTION
				"Allows selecting the switching mode Trap Enable"
		::= { ipa2000c01v1Entry 22 }

		-- 1.3.6.1.4.1.10106.3.101291.1.1.23
		ipa2000c01v1Ch1Prior OBJECT-TYPE
			SYNTAX Uint2
			MAX-ACCESS read-write
			STATUS current
			DESCRIPTION
				"Allows selecting channel input priority"
		::= { ipa2000c01v1Entry 23 }

		-- 1.3.6.1.4.1.10106.3.101291.1.1.24
		ipa2000c01v1Ch1PriorTrapEnable OBJECT-TYPE
			SYNTAX AlarmEnable
			MAX-ACCESS read-write
			STATUS current
			DESCRIPTION
				"Allows selecting channel input priority Trap Enable"
		::= { ipa2000c01v1Entry 24 }

		-- 1.3.6.1.4.1.10106.3.101291.1.1.25
		ipa2000c01v1Ch2Prior OBJECT-TYPE
			SYNTAX Uint2
			MAX-ACCESS read-write
			STATUS current
			DESCRIPTION
				"Allows selecting channel input priority"
		::= { ipa2000c01v1Entry 25 }

		-- 1.3.6.1.4.1.10106.3.101291.1.1.26
		ipa2000c01v1Ch2PriorTrapEnable OBJECT-TYPE
			SYNTAX AlarmEnable
			MAX-ACCESS read-write
			STATUS current
			DESCRIPTION
				"Allows selecting channel input priority Trap Enable"
		::= { ipa2000c01v1Entry 26 }

		-- 1.3.6.1.4.1.10106.3.101291.1.1.27
		ipa2000c01v1MaxTimeOut OBJECT-TYPE
			SYNTAX TimeX1Ms1
			MAX-ACCESS read-write
			STATUS current
			DESCRIPTION
				"Maximum time out for IP channels without receiving any packet.  It limits the low frequency jitter capacity."
		::= { ipa2000c01v1Entry 27 }

		-- 1.3.6.1.4.1.10106.3.101291.1.1.29
		ipa2000c01v1EnSeamNondvbt OBJECT-TYPE
			SYNTAX Bit0No1Yes
			MAX-ACCESS read-write
			STATUS current
			DESCRIPTION
				"Allows enabling seamless mode with non DVB-T signals"
		::= { ipa2000c01v1Entry 29 }

		-- 1.3.6.1.4.1.10106.3.101291.1.1.31
		ipa2000c01v1NarrowPllBw OBJECT-TYPE
			SYNTAX Bit0No1Yes
			MAX-ACCESS read-write
			STATUS current
			DESCRIPTION
				"Allows selecting a narrow PLL bandwidth in the clock packet PLL in non DVB-T mode to achieve a very stable bitrate"
		::= { ipa2000c01v1Entry 31 }

		-- 1.3.6.1.4.1.10106.3.101291.1.1.33
		ipa2000c01v1DvbTMode OBJECT-TYPE
			SYNTAX Bit0No1Yes
			MAX-ACCESS read-write
			STATUS current
			DESCRIPTION
				"Selects DVB-T mode."
		::= { ipa2000c01v1Entry 33 }

		-- 1.3.6.1.4.1.10106.3.101291.1.1.34
		ipa2000c01v1DvbTModeTrapEnable OBJECT-TYPE
			SYNTAX AlarmEnable
			MAX-ACCESS read-write
			STATUS current
			DESCRIPTION
				"Selects DVB-T mode. Trap Enable"
		::= { ipa2000c01v1Entry 34 }

		-- 1.3.6.1.4.1.10106.3.101291.1.1.35
		ipa2000c01v1NullPckRtp OBJECT-TYPE
			SYNTAX Bit0No1Yes
			MAX-ACCESS read-write
			STATUS current
			DESCRIPTION
				"Selects if NULL packets are inserted if there are unrecovered packets when using RTP protocol"
		::= { ipa2000c01v1Entry 35 }

		-- 1.3.6.1.4.1.10106.3.101291.1.1.37
		ipa2000c01v1TxAsi1En OBJECT-TYPE
			SYNTAX InputOutput
			MAX-ACCESS read-write
			STATUS current
			DESCRIPTION
				"ASI 1 interface control"
		::= { ipa2000c01v1Entry 37 }

		-- 1.3.6.1.4.1.10106.3.101291.1.1.39
		ipa2000c01v1TxAsi2En OBJECT-TYPE
			SYNTAX InputOutput
			MAX-ACCESS read-write
			STATUS current
			DESCRIPTION
				"ASI 2 interface control"
		::= { ipa2000c01v1Entry 39 }

		-- 1.3.6.1.4.1.10106.3.101291.1.1.41
		ipa2000c01v1TxAsi1AuxEn OBJECT-TYPE
			SYNTAX InputOutputAux
			MAX-ACCESS read-write
			STATUS current
			DESCRIPTION
				"ASI 1 aux interface control"
		::= { ipa2000c01v1Entry 41 }

		-- 1.3.6.1.4.1.10106.3.101291.1.1.43
		ipa2000c01v1TxAsi2AuxEn OBJECT-TYPE
			SYNTAX InputOutputAux
			MAX-ACCESS read-write
			STATUS current
			DESCRIPTION
				"ASI 2 aux interface control"
		::= { ipa2000c01v1Entry 43 }

		-- 1.3.6.1.4.1.10106.3.101291.1.1.45
		ipa2000c01v1RxIp1Inter OBJECT-TYPE
			SYNTAX IpInterface
			MAX-ACCESS read-write
			STATUS current
			DESCRIPTION
				"Interface selection"
		::= { ipa2000c01v1Entry 45 }

		-- 1.3.6.1.4.1.10106.3.101291.1.1.47
		ipa2000c01v1RxIp2Inter OBJECT-TYPE
			SYNTAX IpInterface
			MAX-ACCESS read-write
			STATUS current
			DESCRIPTION
				"Interface selection"
		::= { ipa2000c01v1Entry 47 }

		-- 1.3.6.1.4.1.10106.3.101291.1.1.49
		ipa2000c01v1TxIp1Inter OBJECT-TYPE
			SYNTAX IpInterface
			MAX-ACCESS read-write
			STATUS current
			DESCRIPTION
				"Interface selection"
		::= { ipa2000c01v1Entry 49 }

		-- 1.3.6.1.4.1.10106.3.101291.1.1.51
		ipa2000c01v1TxIp2Inter OBJECT-TYPE
			SYNTAX IpInterface
			MAX-ACCESS read-write
			STATUS current
			DESCRIPTION
				"Interface selection"
		::= { ipa2000c01v1Entry 51 }

		-- 1.3.6.1.4.1.10106.3.101291.1.1.53
		ipa2000c01v1TxIp1OutSel OBJECT-TYPE
			SYNTAX IpaOutSel
			MAX-ACCESS read-write
			STATUS current
			DESCRIPTION
				"Output selection"
		::= { ipa2000c01v1Entry 53 }

		-- 1.3.6.1.4.1.10106.3.101291.1.1.55
		ipa2000c01v1TxIp2OutSel OBJECT-TYPE
			SYNTAX IpaOutSel
			MAX-ACCESS read-write
			STATUS current
			DESCRIPTION
				"Output selection"
		::= { ipa2000c01v1Entry 55 }

		-- 1.3.6.1.4.1.10106.3.101291.1.1.57
		ipa2000c01v1EthMode1 OBJECT-TYPE
			SYNTAX EthMode2000
			MAX-ACCESS read-write
			STATUS current
			DESCRIPTION
				"Allows selecting the Ethernet operating mode"
		::= { ipa2000c01v1Entry 57 }

		-- 1.3.6.1.4.1.10106.3.101291.1.1.59
		ipa2000c01v1EthMode2 OBJECT-TYPE
			SYNTAX EthMode2000
			MAX-ACCESS read-write
			STATUS current
			DESCRIPTION
				"Allows selecting the Ethernet operating mode"
		::= { ipa2000c01v1Entry 59 }

		-- 1.3.6.1.4.1.10106.3.101291.1.1.61
		ipa2000c01v1Ch1Selection OBJECT-TYPE
			SYNTAX IpaChSelection
			MAX-ACCESS read-write
			STATUS current
			DESCRIPTION
				"Input selection"
		::= { ipa2000c01v1Entry 61 }

		-- 1.3.6.1.4.1.10106.3.101291.1.1.62
		ipa2000c01v1Ch1SelectionTrapEnable OBJECT-TYPE
			SYNTAX AlarmEnable
			MAX-ACCESS read-write
			STATUS current
			DESCRIPTION
				"Input selection Trap Enable"
		::= { ipa2000c01v1Entry 62 }

		-- 1.3.6.1.4.1.10106.3.101291.1.1.63
		ipa2000c01v1Ch2Selection OBJECT-TYPE
			SYNTAX IpaChSelection
			MAX-ACCESS read-write
			STATUS current
			DESCRIPTION
				"Input selection"
		::= { ipa2000c01v1Entry 63 }

		-- 1.3.6.1.4.1.10106.3.101291.1.1.64
		ipa2000c01v1Ch2SelectionTrapEnable OBJECT-TYPE
			SYNTAX AlarmEnable
			MAX-ACCESS read-write
			STATUS current
			DESCRIPTION
				"Input selection Trap Enable"
		::= { ipa2000c01v1Entry 64 }

		-- 1.3.6.1.4.1.10106.3.101291.1.1.65
		ipa2000c01v1TsSyncLossEn OBJECT-TYPE
			SYNTAX Bit0No1Yes
			MAX-ACCESS read-write
			STATUS current
			DESCRIPTION
				"Enables loss of synchronization detection (Fist priority  parameter 1.1)"
		::= { ipa2000c01v1Entry 65 }

		-- 1.3.6.1.4.1.10106.3.101291.1.1.67
		ipa2000c01v1SyncByErrorEn OBJECT-TYPE
			SYNTAX Bit0No1Yes
			MAX-ACCESS read-write
			STATUS current
			DESCRIPTION
				"Enables sync byte error detection (Fist priority  parameter 1.2)"
		::= { ipa2000c01v1Entry 67 }

		-- 1.3.6.1.4.1.10106.3.101291.1.1.69
		ipa2000c01v1PatErrorEn OBJECT-TYPE
			SYNTAX Bit0No1Yes
			MAX-ACCESS read-write
			STATUS current
			DESCRIPTION
				"Enables PAT error detection (Fist priority  parameter 1.3)"
		::= { ipa2000c01v1Entry 69 }

		-- 1.3.6.1.4.1.10106.3.101291.1.1.71
		ipa2000c01v1CcErrorEn OBJECT-TYPE
			SYNTAX Bit0No1Yes
			MAX-ACCESS read-write
			STATUS current
			DESCRIPTION
				"Enables continuity counter error detection (Fist priority  parameter 1.4)"
		::= { ipa2000c01v1Entry 71 }

		-- 1.3.6.1.4.1.10106.3.101291.1.1.73
		ipa2000c01v1PmtErrorEn OBJECT-TYPE
			SYNTAX Bit0No1Yes
			MAX-ACCESS read-write
			STATUS current
			DESCRIPTION
				"Enables PMT error detection (Fist priority  parameter 1.5)"
		::= { ipa2000c01v1Entry 73 }

		-- 1.3.6.1.4.1.10106.3.101291.1.1.75
		ipa2000c01v1PidErrorEn OBJECT-TYPE
			SYNTAX Bit0No1Yes
			MAX-ACCESS read-write
			STATUS current
			DESCRIPTION
				"Enables PID error detection (Fist priority  parameter 1.6)"
		::= { ipa2000c01v1Entry 75 }

		-- 1.3.6.1.4.1.10106.3.101291.1.1.77
		ipa2000c01v1PidErrorTime OBJECT-TYPE
			SYNTAX TimeX1Ms1
			MAX-ACCESS read-write
			STATUS current
			DESCRIPTION
				"PID error time out"
		::= { ipa2000c01v1Entry 77 }

		-- 1.3.6.1.4.1.10106.3.101291.1.1.79
		ipa2000c01v1OutDelay OBJECT-TYPE
			SYNTAX DelayX100Ns
			MAX-ACCESS read-write
			STATUS current
			DESCRIPTION
				"Output delay refered to 1PPS reference in DVB-T mode"
		::= { ipa2000c01v1Entry 79 }

		-- 1.3.6.1.4.1.10106.3.101291.1.1.80
		ipa2000c01v1OutDelayTrapEnable OBJECT-TYPE
			SYNTAX AlarmEnable
			MAX-ACCESS read-write
			STATUS current
			DESCRIPTION
				"Output delay refered to 1PPS reference in DVB-T mode Trap Enable"
		::= { ipa2000c01v1Entry 80 }

		-- 1.3.6.1.4.1.10106.3.101291.1.1.81
		ipa2000c01v1PacketDelay OBJECT-TYPE
			SYNTAX DelayPacket1
			MAX-ACCESS read-write
			STATUS current
			DESCRIPTION
				"Output delay in TS packets in non DVB-T mode"
		::= { ipa2000c01v1Entry 81 }

		-- 1.3.6.1.4.1.10106.3.101291.1.1.82
		ipa2000c01v1PacketDelayTrapEnable OBJECT-TYPE
			SYNTAX AlarmEnable
			MAX-ACCESS read-write
			STATUS current
			DESCRIPTION
				"Output delay in TS packets in non DVB-T mode Trap Enable"
		::= { ipa2000c01v1Entry 82 }

		-- 1.3.6.1.4.1.10106.3.101291.1.1.83
		ipa2000c01v1Str1Ena OBJECT-TYPE
			SYNTAX Bit0No1Yes
			MAX-ACCESS read-write
			STATUS current
			DESCRIPTION
				"Receiver enable"
		::= { ipa2000c01v1Entry 83 }

		-- 1.3.6.1.4.1.10106.3.101291.1.1.85
		ipa2000c01v1Str1MulticEna OBJECT-TYPE
			SYNTAX IpaTxMode
			MAX-ACCESS read-write
			STATUS current
			DESCRIPTION
				"RX mode"
		::= { ipa2000c01v1Entry 85 }

		-- 1.3.6.1.4.1.10106.3.101291.1.1.87
		ipa2000c01v1Str1FecEna OBJECT-TYPE
			SYNTAX Bit0No1Yes
			MAX-ACCESS read-write
			STATUS current
			DESCRIPTION
				"Enable FEC"
		::= { ipa2000c01v1Entry 87 }

		-- 1.3.6.1.4.1.10106.3.101291.1.1.89
		ipa2000c01v1Str1UipDAdd3 OBJECT-TYPE
			SYNTAX Uint8
			MAX-ACCESS read-write
			STATUS current
			DESCRIPTION
				"IP address (3)"
		::= { ipa2000c01v1Entry 89 }

		-- 1.3.6.1.4.1.10106.3.101291.1.1.91
		ipa2000c01v1Str1UipDAdd2 OBJECT-TYPE
			SYNTAX Uint8
			MAX-ACCESS read-write
			STATUS current
			DESCRIPTION
				"IP address (2)"
		::= { ipa2000c01v1Entry 91 }

		-- 1.3.6.1.4.1.10106.3.101291.1.1.93
		ipa2000c01v1Str1UipDAdd1 OBJECT-TYPE
			SYNTAX Uint8
			MAX-ACCESS read-write
			STATUS current
			DESCRIPTION
				"IP address (1)"
		::= { ipa2000c01v1Entry 93 }

		-- 1.3.6.1.4.1.10106.3.101291.1.1.95
		ipa2000c01v1Str1UipDAdd0 OBJECT-TYPE
			SYNTAX Uint8
			MAX-ACCESS read-write
			STATUS current
			DESCRIPTION
				"IP address (0)"
		::= { ipa2000c01v1Entry 95 }

		-- 1.3.6.1.4.1.10106.3.101291.1.1.97
		ipa2000c01v1Str1MipDAdd3 OBJECT-TYPE
			SYNTAX Uint8
			MAX-ACCESS read-write
			STATUS current
			DESCRIPTION
				"Multicast IP address (3)"
		::= { ipa2000c01v1Entry 97 }

		-- 1.3.6.1.4.1.10106.3.101291.1.1.99
		ipa2000c01v1Str1MipDAdd2 OBJECT-TYPE
			SYNTAX Uint8
			MAX-ACCESS read-write
			STATUS current
			DESCRIPTION
				"Multicast IP address (2)"
		::= { ipa2000c01v1Entry 99 }

		-- 1.3.6.1.4.1.10106.3.101291.1.1.101
		ipa2000c01v1Str1MipDAdd1 OBJECT-TYPE
			SYNTAX Uint8
			MAX-ACCESS read-write
			STATUS current
			DESCRIPTION
				"Multicast IP address (1)"
		::= { ipa2000c01v1Entry 101 }

		-- 1.3.6.1.4.1.10106.3.101291.1.1.103
		ipa2000c01v1Str1MipDAdd0 OBJECT-TYPE
			SYNTAX Uint8
			MAX-ACCESS read-write
			STATUS current
			DESCRIPTION
				"Multicast IP address (0)"
		::= { ipa2000c01v1Entry 103 }

		-- 1.3.6.1.4.1.10106.3.101291.1.1.105
		ipa2000c01v1Str1IgmFAdd3 OBJECT-TYPE
			SYNTAX Uint8
			MAX-ACCESS read-write
			STATUS current
			DESCRIPTION
				"Source IP address (3)"
		::= { ipa2000c01v1Entry 105 }

		-- 1.3.6.1.4.1.10106.3.101291.1.1.107
		ipa2000c01v1Str1IgmFAdd2 OBJECT-TYPE
			SYNTAX Uint8
			MAX-ACCESS read-write
			STATUS current
			DESCRIPTION
				"Source IP address (2)"
		::= { ipa2000c01v1Entry 107 }

		-- 1.3.6.1.4.1.10106.3.101291.1.1.109
		ipa2000c01v1Str1IgmFAdd1 OBJECT-TYPE
			SYNTAX Uint8
			MAX-ACCESS read-write
			STATUS current
			DESCRIPTION
				"Source IP address (1)"
		::= { ipa2000c01v1Entry 109 }

		-- 1.3.6.1.4.1.10106.3.101291.1.1.111
		ipa2000c01v1Str1IgmFAdd0 OBJECT-TYPE
			SYNTAX Uint8
			MAX-ACCESS read-write
			STATUS current
			DESCRIPTION
				"Source IP address (0)"
		::= { ipa2000c01v1Entry 111 }

		-- 1.3.6.1.4.1.10106.3.101291.1.1.113
		ipa2000c01v1Str1DPort OBJECT-TYPE
			SYNTAX Uint16
			MAX-ACCESS read-write
			STATUS current
			DESCRIPTION
				"Destination port"
		::= { ipa2000c01v1Entry 113 }

		-- 1.3.6.1.4.1.10106.3.101291.1.1.115
		ipa2000c01v1RxIp1SrMsk OBJECT-TYPE
			SYNTAX Uint8
			MAX-ACCESS read-write
			STATUS current
			DESCRIPTION
				"IP address mask (3)"
		::= { ipa2000c01v1Entry 115 }

		-- 1.3.6.1.4.1.10106.3.101291.1.1.117
		ipa2000c01v1RxIp1SrMsk2 OBJECT-TYPE
			SYNTAX Uint8
			MAX-ACCESS read-write
			STATUS current
			DESCRIPTION
				"IP address mask (2)"
		::= { ipa2000c01v1Entry 117 }

		-- 1.3.6.1.4.1.10106.3.101291.1.1.119
		ipa2000c01v1RxIp1SrMsk1 OBJECT-TYPE
			SYNTAX Uint8
			MAX-ACCESS read-write
			STATUS current
			DESCRIPTION
				"IP address mask (1)"
		::= { ipa2000c01v1Entry 119 }

		-- 1.3.6.1.4.1.10106.3.101291.1.1.121
		ipa2000c01v1RxIp1SrMsk0 OBJECT-TYPE
			SYNTAX Uint8
			MAX-ACCESS read-write
			STATUS current
			DESCRIPTION
				"IP address mask (0)"
		::= { ipa2000c01v1Entry 121 }

		-- 1.3.6.1.4.1.10106.3.101291.1.1.123
		ipa2000c01v1Str2Ena OBJECT-TYPE
			SYNTAX Bit0No1Yes
			MAX-ACCESS read-write
			STATUS current
			DESCRIPTION
				"Receiver enable"
		::= { ipa2000c01v1Entry 123 }

		-- 1.3.6.1.4.1.10106.3.101291.1.1.125
		ipa2000c01v1Str2MulticEna OBJECT-TYPE
			SYNTAX IpaTxMode
			MAX-ACCESS read-write
			STATUS current
			DESCRIPTION
				"RX mode"
		::= { ipa2000c01v1Entry 125 }

		-- 1.3.6.1.4.1.10106.3.101291.1.1.127
		ipa2000c01v1Str2FecEna OBJECT-TYPE
			SYNTAX Bit0No1Yes
			MAX-ACCESS read-write
			STATUS current
			DESCRIPTION
				"Enable FEC"
		::= { ipa2000c01v1Entry 127 }

		-- 1.3.6.1.4.1.10106.3.101291.1.1.129
		ipa2000c01v1Str2UipDAdd3 OBJECT-TYPE
			SYNTAX Uint8
			MAX-ACCESS read-write
			STATUS current
			DESCRIPTION
				"IP address (3)"
		::= { ipa2000c01v1Entry 129 }

		-- 1.3.6.1.4.1.10106.3.101291.1.1.131
		ipa2000c01v1Str2UipDAdd2 OBJECT-TYPE
			SYNTAX Uint8
			MAX-ACCESS read-write
			STATUS current
			DESCRIPTION
				"IP address (2)"
		::= { ipa2000c01v1Entry 131 }

		-- 1.3.6.1.4.1.10106.3.101291.1.1.133
		ipa2000c01v1Str2UipDAdd1 OBJECT-TYPE
			SYNTAX Uint8
			MAX-ACCESS read-write
			STATUS current
			DESCRIPTION
				"IP address (1)"
		::= { ipa2000c01v1Entry 133 }

		-- 1.3.6.1.4.1.10106.3.101291.1.1.135
		ipa2000c01v1Str2UipDAdd0 OBJECT-TYPE
			SYNTAX Uint8
			MAX-ACCESS read-write
			STATUS current
			DESCRIPTION
				"IP address (0)"
		::= { ipa2000c01v1Entry 135 }

		-- 1.3.6.1.4.1.10106.3.101291.1.1.137
		ipa2000c01v1Str2MipDAdd3 OBJECT-TYPE
			SYNTAX Uint8
			MAX-ACCESS read-write
			STATUS current
			DESCRIPTION
				"Multicast IP address (3)"
		::= { ipa2000c01v1Entry 137 }

		-- 1.3.6.1.4.1.10106.3.101291.1.1.139
		ipa2000c01v1Str2MipDAdd2 OBJECT-TYPE
			SYNTAX Uint8
			MAX-ACCESS read-write
			STATUS current
			DESCRIPTION
				"Multicast IP address (2)"
		::= { ipa2000c01v1Entry 139 }

		-- 1.3.6.1.4.1.10106.3.101291.1.1.141
		ipa2000c01v1Str2MipDAdd1 OBJECT-TYPE
			SYNTAX Uint8
			MAX-ACCESS read-write
			STATUS current
			DESCRIPTION
				"Multicast IP address (1)"
		::= { ipa2000c01v1Entry 141 }

		-- 1.3.6.1.4.1.10106.3.101291.1.1.143
		ipa2000c01v1Str2MipDAdd0 OBJECT-TYPE
			SYNTAX Uint8
			MAX-ACCESS read-write
			STATUS current
			DESCRIPTION
				"Multicast IP address (0)"
		::= { ipa2000c01v1Entry 143 }

		-- 1.3.6.1.4.1.10106.3.101291.1.1.145
		ipa2000c01v1Str2IgmFAdd3 OBJECT-TYPE
			SYNTAX Uint8
			MAX-ACCESS read-write
			STATUS current
			DESCRIPTION
				"Source IP address (3)"
		::= { ipa2000c01v1Entry 145 }

		-- 1.3.6.1.4.1.10106.3.101291.1.1.147
		ipa2000c01v1Str2IgmFAdd2 OBJECT-TYPE
			SYNTAX Uint8
			MAX-ACCESS read-write
			STATUS current
			DESCRIPTION
				"Source IP address (2)"
		::= { ipa2000c01v1Entry 147 }

		-- 1.3.6.1.4.1.10106.3.101291.1.1.149
		ipa2000c01v1Str2IgmFAdd1 OBJECT-TYPE
			SYNTAX Uint8
			MAX-ACCESS read-write
			STATUS current
			DESCRIPTION
				"Source IP address (1)"
		::= { ipa2000c01v1Entry 149 }

		-- 1.3.6.1.4.1.10106.3.101291.1.1.151
		ipa2000c01v1Str2IgmFAdd0 OBJECT-TYPE
			SYNTAX Uint8
			MAX-ACCESS read-write
			STATUS current
			DESCRIPTION
				"Source IP address (0)"
		::= { ipa2000c01v1Entry 151 }

		-- 1.3.6.1.4.1.10106.3.101291.1.1.153
		ipa2000c01v1Str2DPort OBJECT-TYPE
			SYNTAX Uint16
			MAX-ACCESS read-write
			STATUS current
			DESCRIPTION
				"Destination port"
		::= { ipa2000c01v1Entry 153 }

		-- 1.3.6.1.4.1.10106.3.101291.1.1.155
		ipa2000c01v1RxIp2SrMsk OBJECT-TYPE
			SYNTAX Uint8
			MAX-ACCESS read-write
			STATUS current
			DESCRIPTION
				"IP address mask (3)"
		::= { ipa2000c01v1Entry 155 }

		-- 1.3.6.1.4.1.10106.3.101291.1.1.157
		ipa2000c01v1RxIp2SrMsk1 OBJECT-TYPE
			SYNTAX Uint8
			MAX-ACCESS read-write
			STATUS current
			DESCRIPTION
				"IP address mask (2)"
		::= { ipa2000c01v1Entry 157 }

		-- 1.3.6.1.4.1.10106.3.101291.1.1.159
		ipa2000c01v1RxIp2SrMsk2 OBJECT-TYPE
			SYNTAX Uint8
			MAX-ACCESS read-write
			STATUS current
			DESCRIPTION
				"IP address mask (1)"
		::= { ipa2000c01v1Entry 159 }

		-- 1.3.6.1.4.1.10106.3.101291.1.1.161
		ipa2000c01v1RxIp2SrMsk3 OBJECT-TYPE
			SYNTAX Uint8
			MAX-ACCESS read-write
			STATUS current
			DESCRIPTION
				"IP address mask (0)"
		::= { ipa2000c01v1Entry 161 }

		-- 1.3.6.1.4.1.10106.3.101291.1.1.163
		ipa2000c01v1Tx1UniEna OBJECT-TYPE
			SYNTAX Bit0No1Yes
			MAX-ACCESS read-write
			STATUS current
			DESCRIPTION
				"Enable TX"
		::= { ipa2000c01v1Entry 163 }

		-- 1.3.6.1.4.1.10106.3.101291.1.1.165
		ipa2000c01v1Tx1MultiEna OBJECT-TYPE
			SYNTAX IpaTxMode
			MAX-ACCESS read-write
			STATUS current
			DESCRIPTION
				"TX mode"
		::= { ipa2000c01v1Entry 165 }

		-- 1.3.6.1.4.1.10106.3.101291.1.1.167
		ipa2000c01v1Tx1MipAdd3 OBJECT-TYPE
			SYNTAX Uint8
			MAX-ACCESS read-write
			STATUS current
			DESCRIPTION
				"Multicast dest. IP address (3)"
		::= { ipa2000c01v1Entry 167 }

		-- 1.3.6.1.4.1.10106.3.101291.1.1.169
		ipa2000c01v1Tx1MipAdd2 OBJECT-TYPE
			SYNTAX Uint8
			MAX-ACCESS read-write
			STATUS current
			DESCRIPTION
				"Multicast dest. IP address (2)"
		::= { ipa2000c01v1Entry 169 }

		-- 1.3.6.1.4.1.10106.3.101291.1.1.171
		ipa2000c01v1Tx1MipAdd1 OBJECT-TYPE
			SYNTAX Uint8
			MAX-ACCESS read-write
			STATUS current
			DESCRIPTION
				"Multicast dest. IP address (1)"
		::= { ipa2000c01v1Entry 171 }

		-- 1.3.6.1.4.1.10106.3.101291.1.1.173
		ipa2000c01v1Tx1MipAdd0 OBJECT-TYPE
			SYNTAX Uint8
			MAX-ACCESS read-write
			STATUS current
			DESCRIPTION
				"Multicast dest. IP address (0)"
		::= { ipa2000c01v1Entry 173 }

		-- 1.3.6.1.4.1.10106.3.101291.1.1.175
		ipa2000c01v1Tx1UipAdd3 OBJECT-TYPE
			SYNTAX Uint8
			MAX-ACCESS read-write
			STATUS current
			DESCRIPTION
				"Destination IP address (3)"
		::= { ipa2000c01v1Entry 175 }

		-- 1.3.6.1.4.1.10106.3.101291.1.1.177
		ipa2000c01v1Tx1UipAdd2 OBJECT-TYPE
			SYNTAX Uint8
			MAX-ACCESS read-write
			STATUS current
			DESCRIPTION
				"Destination IP address (2)"
		::= { ipa2000c01v1Entry 177 }

		-- 1.3.6.1.4.1.10106.3.101291.1.1.179
		ipa2000c01v1Tx1UipAdd1 OBJECT-TYPE
			SYNTAX Uint8
			MAX-ACCESS read-write
			STATUS current
			DESCRIPTION
				"Destination IP address (1)"
		::= { ipa2000c01v1Entry 179 }

		-- 1.3.6.1.4.1.10106.3.101291.1.1.181
		ipa2000c01v1Tx1UipAdd0 OBJECT-TYPE
			SYNTAX Uint8
			MAX-ACCESS read-write
			STATUS current
			DESCRIPTION
				"Destination IP address (0)"
		::= { ipa2000c01v1Entry 181 }

		-- 1.3.6.1.4.1.10106.3.101291.1.1.183
		ipa2000c01v1Tx1SPort OBJECT-TYPE
			SYNTAX Uint16
			MAX-ACCESS read-write
			STATUS current
			DESCRIPTION
				"Source port"
		::= { ipa2000c01v1Entry 183 }

		-- 1.3.6.1.4.1.10106.3.101291.1.1.185
		ipa2000c01v1Tx1DPort OBJECT-TYPE
			SYNTAX Uint16
			MAX-ACCESS read-write
			STATUS current
			DESCRIPTION
				"Destination port"
		::= { ipa2000c01v1Entry 185 }

		-- 1.3.6.1.4.1.10106.3.101291.1.1.187
		ipa2000c01v1Tx1LParam OBJECT-TYPE
			SYNTAX Uint5
			MAX-ACCESS read-write
			STATUS current
			DESCRIPTION
				"L parameter (FEC mode columns)"
		::= { ipa2000c01v1Entry 187 }

		-- 1.3.6.1.4.1.10106.3.101291.1.1.189
		ipa2000c01v1Tx1FecMode OBJECT-TYPE
			SYNTAX FecMode
			MAX-ACCESS read-write
			STATUS current
			DESCRIPTION
				"Protocol"
		::= { ipa2000c01v1Entry 189 }

		-- 1.3.6.1.4.1.10106.3.101291.1.1.191
		ipa2000c01v1Tx1DParam OBJECT-TYPE
			SYNTAX Uint5
			MAX-ACCESS read-write
			STATUS current
			DESCRIPTION
				"D parameter (FEC mode rows)"
		::= { ipa2000c01v1Entry 191 }

		-- 1.3.6.1.4.1.10106.3.101291.1.1.193
		ipa2000c01v1Tx1TspkInIppk OBJECT-TYPE
			SYNTAX Uint3
			MAX-ACCESS read-write
			STATUS current
			DESCRIPTION
				"TS packets in each IP packet"
		::= { ipa2000c01v1Entry 193 }

		-- 1.3.6.1.4.1.10106.3.101291.1.1.195
		ipa2000c01v1Tx1RowDelay OBJECT-TYPE
			SYNTAX Uint5
			MAX-ACCESS read-write
			STATUS current
			DESCRIPTION
				"FEC row delay"
		::= { ipa2000c01v1Entry 195 }

		-- 1.3.6.1.4.1.10106.3.101291.1.1.197
		ipa2000c01v1Tx1ColDelay OBJECT-TYPE
			SYNTAX Uint8
			MAX-ACCESS read-write
			STATUS current
			DESCRIPTION
				"FEC column delay"
		::= { ipa2000c01v1Entry 197 }

		-- 1.3.6.1.4.1.10106.3.101291.1.1.199
		ipa2000c01v1TxIp1SrAdd3 OBJECT-TYPE
			SYNTAX Uint8
			MAX-ACCESS read-write
			STATUS current
			DESCRIPTION
				"Source IP address (3)"
		::= { ipa2000c01v1Entry 199 }

		-- 1.3.6.1.4.1.10106.3.101291.1.1.201
		ipa2000c01v1TxIp1SrAdd2 OBJECT-TYPE
			SYNTAX Uint8
			MAX-ACCESS read-write
			STATUS current
			DESCRIPTION
				"Source IP address (2)"
		::= { ipa2000c01v1Entry 201 }

		-- 1.3.6.1.4.1.10106.3.101291.1.1.203
		ipa2000c01v1TxIp1SrAdd1 OBJECT-TYPE
			SYNTAX Uint8
			MAX-ACCESS read-write
			STATUS current
			DESCRIPTION
				"Source IP address (1)"
		::= { ipa2000c01v1Entry 203 }

		-- 1.3.6.1.4.1.10106.3.101291.1.1.205
		ipa2000c01v1TxIp1SrAdd0 OBJECT-TYPE
			SYNTAX Uint8
			MAX-ACCESS read-write
			STATUS current
			DESCRIPTION
				"Source IP address (0)"
		::= { ipa2000c01v1Entry 205 }

		-- 1.3.6.1.4.1.10106.3.101291.1.1.207
		ipa2000c01v1TxIp1SrMsk0 OBJECT-TYPE
			SYNTAX Uint8
			MAX-ACCESS read-write
			STATUS current
			DESCRIPTION
				"Source IP address mask (3)"
		::= { ipa2000c01v1Entry 207 }

		-- 1.3.6.1.4.1.10106.3.101291.1.1.209
		ipa2000c01v1TxIp1SrMsk1 OBJECT-TYPE
			SYNTAX Uint8
			MAX-ACCESS read-write
			STATUS current
			DESCRIPTION
				"Source IP address mask (2)"
		::= { ipa2000c01v1Entry 209 }

		-- 1.3.6.1.4.1.10106.3.101291.1.1.211
		ipa2000c01v1TxIp1SrMsk2 OBJECT-TYPE
			SYNTAX Uint8
			MAX-ACCESS read-write
			STATUS current
			DESCRIPTION
				"Source IP address mask (1)"
		::= { ipa2000c01v1Entry 211 }

		-- 1.3.6.1.4.1.10106.3.101291.1.1.213
		ipa2000c01v1TxIp1SrMsk3 OBJECT-TYPE
			SYNTAX Uint8
			MAX-ACCESS read-write
			STATUS current
			DESCRIPTION
				"Source IP address mask (0)"
		::= { ipa2000c01v1Entry 213 }

		-- 1.3.6.1.4.1.10106.3.101291.1.1.215
		ipa2000c01v1Tx2UniEna OBJECT-TYPE
			SYNTAX Bit0No1Yes
			MAX-ACCESS read-write
			STATUS current
			DESCRIPTION
				"Enable TX"
		::= { ipa2000c01v1Entry 215 }

		-- 1.3.6.1.4.1.10106.3.101291.1.1.217
		ipa2000c01v1Tx2MultiEna OBJECT-TYPE
			SYNTAX IpaTxMode
			MAX-ACCESS read-write
			STATUS current
			DESCRIPTION
				"TX mode"
		::= { ipa2000c01v1Entry 217 }

		-- 1.3.6.1.4.1.10106.3.101291.1.1.219
		ipa2000c01v1Tx2MipAdd3 OBJECT-TYPE
			SYNTAX Uint8
			MAX-ACCESS read-write
			STATUS current
			DESCRIPTION
				"Multicast dest. IP address (3)"
		::= { ipa2000c01v1Entry 219 }

		-- 1.3.6.1.4.1.10106.3.101291.1.1.221
		ipa2000c01v1Tx2MipAdd2 OBJECT-TYPE
			SYNTAX Uint8
			MAX-ACCESS read-write
			STATUS current
			DESCRIPTION
				"Multicast dest. IP address (2)"
		::= { ipa2000c01v1Entry 221 }

		-- 1.3.6.1.4.1.10106.3.101291.1.1.223
		ipa2000c01v1Tx2MipAdd1 OBJECT-TYPE
			SYNTAX Uint8
			MAX-ACCESS read-write
			STATUS current
			DESCRIPTION
				"Multicast dest. IP address (1)"
		::= { ipa2000c01v1Entry 223 }

		-- 1.3.6.1.4.1.10106.3.101291.1.1.225
		ipa2000c01v1Tx2MipAdd0 OBJECT-TYPE
			SYNTAX Uint8
			MAX-ACCESS read-write
			STATUS current
			DESCRIPTION
				"Multicast dest. IP address (0)"
		::= { ipa2000c01v1Entry 225 }

		-- 1.3.6.1.4.1.10106.3.101291.1.1.227
		ipa2000c01v1Tx2UipAdd3 OBJECT-TYPE
			SYNTAX Uint8
			MAX-ACCESS read-write
			STATUS current
			DESCRIPTION
				"Destination IP address (3)"
		::= { ipa2000c01v1Entry 227 }

		-- 1.3.6.1.4.1.10106.3.101291.1.1.229
		ipa2000c01v1Tx2UipAdd2 OBJECT-TYPE
			SYNTAX Uint8
			MAX-ACCESS read-write
			STATUS current
			DESCRIPTION
				"Destination IP address (2)"
		::= { ipa2000c01v1Entry 229 }

		-- 1.3.6.1.4.1.10106.3.101291.1.1.231
		ipa2000c01v1Tx2UipAdd1 OBJECT-TYPE
			SYNTAX Uint8
			MAX-ACCESS read-write
			STATUS current
			DESCRIPTION
				"Destination IP address (1)"
		::= { ipa2000c01v1Entry 231 }

		-- 1.3.6.1.4.1.10106.3.101291.1.1.233
		ipa2000c01v1Tx2UipAdd0 OBJECT-TYPE
			SYNTAX Uint8
			MAX-ACCESS read-write
			STATUS current
			DESCRIPTION
				"Destination IP address (0)"
		::= { ipa2000c01v1Entry 233 }

		-- 1.3.6.1.4.1.10106.3.101291.1.1.235
		ipa2000c01v1Tx2SPort OBJECT-TYPE
			SYNTAX Uint16
			MAX-ACCESS read-write
			STATUS current
			DESCRIPTION
				"Source port"
		::= { ipa2000c01v1Entry 235 }

		-- 1.3.6.1.4.1.10106.3.101291.1.1.237
		ipa2000c01v1Tx2DPort OBJECT-TYPE
			SYNTAX Uint16
			MAX-ACCESS read-write
			STATUS current
			DESCRIPTION
				"Destination port"
		::= { ipa2000c01v1Entry 237 }

		-- 1.3.6.1.4.1.10106.3.101291.1.1.239
		ipa2000c01v1Tx2LParam OBJECT-TYPE
			SYNTAX Uint5
			MAX-ACCESS read-write
			STATUS current
			DESCRIPTION
				"L parameter (FEC mode columns)"
		::= { ipa2000c01v1Entry 239 }

		-- 1.3.6.1.4.1.10106.3.101291.1.1.241
		ipa2000c01v1Tx2FecMode OBJECT-TYPE
			SYNTAX FecMode
			MAX-ACCESS read-write
			STATUS current
			DESCRIPTION
				"Protocol"
		::= { ipa2000c01v1Entry 241 }

		-- 1.3.6.1.4.1.10106.3.101291.1.1.243
		ipa2000c01v1Tx2DParam OBJECT-TYPE
			SYNTAX Uint5
			MAX-ACCESS read-write
			STATUS current
			DESCRIPTION
				"D parameter (FEC mode rows)"
		::= { ipa2000c01v1Entry 243 }

		-- 1.3.6.1.4.1.10106.3.101291.1.1.245
		ipa2000c01v1Tx2TspkInIppk OBJECT-TYPE
			SYNTAX Uint3
			MAX-ACCESS read-write
			STATUS current
			DESCRIPTION
				"TS packets in each IP packet"
		::= { ipa2000c01v1Entry 245 }

		-- 1.3.6.1.4.1.10106.3.101291.1.1.247
		ipa2000c01v1Tx2RowDelay OBJECT-TYPE
			SYNTAX Uint5
			MAX-ACCESS read-write
			STATUS current
			DESCRIPTION
				"FEC row delay"
		::= { ipa2000c01v1Entry 247 }

		-- 1.3.6.1.4.1.10106.3.101291.1.1.249
		ipa2000c01v1Tx2ColDelay OBJECT-TYPE
			SYNTAX Uint8
			MAX-ACCESS read-write
			STATUS current
			DESCRIPTION
				"FEC column delay"
		::= { ipa2000c01v1Entry 249 }

		-- 1.3.6.1.4.1.10106.3.101291.1.1.251
		ipa2000c01v1TxIp2SrAdd3 OBJECT-TYPE
			SYNTAX Uint8
			MAX-ACCESS read-write
			STATUS current
			DESCRIPTION
				"Source IP address (3)"
		::= { ipa2000c01v1Entry 251 }

		-- 1.3.6.1.4.1.10106.3.101291.1.1.253
		ipa2000c01v1TxIp2SrAdd2 OBJECT-TYPE
			SYNTAX Uint8
			MAX-ACCESS read-write
			STATUS current
			DESCRIPTION
				"Source IP address (2)"
		::= { ipa2000c01v1Entry 253 }

		-- 1.3.6.1.4.1.10106.3.101291.1.1.255
		ipa2000c01v1TxIp2SrAdd1 OBJECT-TYPE
			SYNTAX Uint8
			MAX-ACCESS read-write
			STATUS current
			DESCRIPTION
				"Source IP address (1)"
		::= { ipa2000c01v1Entry 255 }

		-- 1.3.6.1.4.1.10106.3.101291.1.1.257
		ipa2000c01v1TxIp2SrAdd0 OBJECT-TYPE
			SYNTAX Uint8
			MAX-ACCESS read-write
			STATUS current
			DESCRIPTION
				"Source IP address (0)"
		::= { ipa2000c01v1Entry 257 }

		-- 1.3.6.1.4.1.10106.3.101291.1.1.259
		ipa2000c01v1TxIp2SrMsk0 OBJECT-TYPE
			SYNTAX Uint8
			MAX-ACCESS read-write
			STATUS current
			DESCRIPTION
				"Source IP address mask (3)"
		::= { ipa2000c01v1Entry 259 }

		-- 1.3.6.1.4.1.10106.3.101291.1.1.261
		ipa2000c01v1TxIp2SrMsk1 OBJECT-TYPE
			SYNTAX Uint8
			MAX-ACCESS read-write
			STATUS current
			DESCRIPTION
				"Source IP address mask (2)"
		::= { ipa2000c01v1Entry 261 }

		-- 1.3.6.1.4.1.10106.3.101291.1.1.263
		ipa2000c01v1TxIp2SrMsk2 OBJECT-TYPE
			SYNTAX Uint8
			MAX-ACCESS read-write
			STATUS current
			DESCRIPTION
				"Source IP address mask (1)"
		::= { ipa2000c01v1Entry 263 }

		-- 1.3.6.1.4.1.10106.3.101291.1.1.265
		ipa2000c01v1TxIp2SrMsk3 OBJECT-TYPE
			SYNTAX Uint8
			MAX-ACCESS read-write
			STATUS current
			DESCRIPTION
				"Source IP address mask (0)"
		::= { ipa2000c01v1Entry 265 }

		-- 1.3.6.1.4.1.10106.3.101291.1.1.267
		ipa2000c01v1Rx1IpRxAdd3 OBJECT-TYPE
			SYNTAX Uint8
			MAX-ACCESS read-only
			STATUS current
			DESCRIPTION
				"RX packets source IP address (3)"
		::= { ipa2000c01v1Entry 267 }

		-- 1.3.6.1.4.1.10106.3.101291.1.1.269
		ipa2000c01v1Rx1IpRxAdd2 OBJECT-TYPE
			SYNTAX Uint8
			MAX-ACCESS read-only
			STATUS current
			DESCRIPTION
				"RX packets source IP address (2)"
		::= { ipa2000c01v1Entry 269 }

		-- 1.3.6.1.4.1.10106.3.101291.1.1.271
		ipa2000c01v1Rx1IpRxAdd1 OBJECT-TYPE
			SYNTAX Uint8
			MAX-ACCESS read-only
			STATUS current
			DESCRIPTION
				"RX packets source IP address (1)"
		::= { ipa2000c01v1Entry 271 }

		-- 1.3.6.1.4.1.10106.3.101291.1.1.273
		ipa2000c01v1Rx1IpRxAdd0 OBJECT-TYPE
			SYNTAX Uint8
			MAX-ACCESS read-only
			STATUS current
			DESCRIPTION
				"RX packets source IP address (0)"
		::= { ipa2000c01v1Entry 273 }

		-- 1.3.6.1.4.1.10106.3.101291.1.1.275
		ipa2000c01v1Rx1IpRxPort OBJECT-TYPE
			SYNTAX Uint16
			MAX-ACCESS read-only
			STATUS current
			DESCRIPTION
				"RX packets UDP source port"
		::= { ipa2000c01v1Entry 275 }

		-- 1.3.6.1.4.1.10106.3.101291.1.1.277
		ipa2000c01v1Rx1LParam OBJECT-TYPE
			SYNTAX Uint5
			MAX-ACCESS read-only
			STATUS current
			DESCRIPTION
				"L parameter (FEC mode columns)"
		::= { ipa2000c01v1Entry 277 }

		-- 1.3.6.1.4.1.10106.3.101291.1.1.279
		ipa2000c01v1Rx1FecMode OBJECT-TYPE
			SYNTAX FecMode
			MAX-ACCESS read-only
			STATUS current
			DESCRIPTION
				"Protocol"
		::= { ipa2000c01v1Entry 279 }

		-- 1.3.6.1.4.1.10106.3.101291.1.1.281
		ipa2000c01v1Rx1PacketSize OBJECT-TYPE
			SYNTAX Bit02041188
			MAX-ACCESS read-only
			STATUS current
			DESCRIPTION
				"Bytes in TS packets"
		::= { ipa2000c01v1Entry 281 }

		-- 1.3.6.1.4.1.10106.3.101291.1.1.283
		ipa2000c01v1Rx1DParam OBJECT-TYPE
			SYNTAX Uint5
			MAX-ACCESS read-only
			STATUS current
			DESCRIPTION
				"D parameter (FEC mode rows)"
		::= { ipa2000c01v1Entry 283 }

		-- 1.3.6.1.4.1.10106.3.101291.1.1.285
		ipa2000c01v1Rx1TsPcks OBJECT-TYPE
			SYNTAX Uint3
			MAX-ACCESS read-only
			STATUS current
			DESCRIPTION
				"TS packets in each IP packet"
		::= { ipa2000c01v1Entry 285 }

		-- 1.3.6.1.4.1.10106.3.101291.1.1.287
		ipa2000c01v1Rx1PacketRate OBJECT-TYPE
			SYNTAX PacketRate
			MAX-ACCESS read-only
			STATUS current
			DESCRIPTION
				"IP packet rate"
		::= { ipa2000c01v1Entry 287 }

		-- 1.3.6.1.4.1.10106.3.101291.1.1.289
		ipa2000c01v1Rx1FecRate OBJECT-TYPE
			SYNTAX PacketRate
			MAX-ACCESS read-only
			STATUS current
			DESCRIPTION
				"FEC packet rate"
		::= { ipa2000c01v1Entry 289 }

		-- 1.3.6.1.4.1.10106.3.101291.1.1.291
		ipa2000c01v1Rx1TimeRst OBJECT-TYPE
			SYNTAX TimeS4
			MAX-ACCESS read-only
			STATUS current
			DESCRIPTION
				"Elapsed time since last reset"
		::= { ipa2000c01v1Entry 291 }

		-- 1.3.6.1.4.1.10106.3.101291.1.1.293
		ipa2000c01v1Rx1LostIpPck OBJECT-TYPE
			SYNTAX Uint16
			MAX-ACCESS read-only
			STATUS current
			DESCRIPTION
				"Lost IP packets"
		::= { ipa2000c01v1Entry 293 }

		-- 1.3.6.1.4.1.10106.3.101291.1.1.295
		ipa2000c01v1Rx1RecIpPck OBJECT-TYPE
			SYNTAX Uint16
			MAX-ACCESS read-only
			STATUS current
			DESCRIPTION
				"Recovered IP packets"
		::= { ipa2000c01v1Entry 295 }

		-- 1.3.6.1.4.1.10106.3.101291.1.1.297
		ipa2000c01v1Rx1OutOrdPck OBJECT-TYPE
			SYNTAX Uint16
			MAX-ACCESS read-only
			STATUS current
			DESCRIPTION
				"Out of order IP packets"
		::= { ipa2000c01v1Entry 297 }

		-- 1.3.6.1.4.1.10106.3.101291.1.1.299
		ipa2000c01v1Rx1BufferStat OBJECT-TYPE
			SYNTAX Rate1
			MAX-ACCESS read-only
			STATUS current
			DESCRIPTION
				"Buffer filling status in non DVB-T mode (with respecto to the central value)"
		::= { ipa2000c01v1Entry 299 }

		-- 1.3.6.1.4.1.10106.3.101291.1.1.301
		ipa2000c01v1Rx2IpRxAdd3 OBJECT-TYPE
			SYNTAX Uint8
			MAX-ACCESS read-only
			STATUS current
			DESCRIPTION
				"RX packets source IP address (3)"
		::= { ipa2000c01v1Entry 301 }

		-- 1.3.6.1.4.1.10106.3.101291.1.1.303
		ipa2000c01v1Rx2IpRxAdd2 OBJECT-TYPE
			SYNTAX Uint8
			MAX-ACCESS read-only
			STATUS current
			DESCRIPTION
				"RX packets source IP address (2)"
		::= { ipa2000c01v1Entry 303 }

		-- 1.3.6.1.4.1.10106.3.101291.1.1.305
		ipa2000c01v1Rx2IpRxAdd1 OBJECT-TYPE
			SYNTAX Uint8
			MAX-ACCESS read-only
			STATUS current
			DESCRIPTION
				"RX packets source IP address (1)"
		::= { ipa2000c01v1Entry 305 }

		-- 1.3.6.1.4.1.10106.3.101291.1.1.307
		ipa2000c01v1Rx2IpRxAdd0 OBJECT-TYPE
			SYNTAX Uint8
			MAX-ACCESS read-only
			STATUS current
			DESCRIPTION
				"RX packets source IP address (0)"
		::= { ipa2000c01v1Entry 307 }

		-- 1.3.6.1.4.1.10106.3.101291.1.1.309
		ipa2000c01v1Rx2IpRxPort OBJECT-TYPE
			SYNTAX Uint16
			MAX-ACCESS read-only
			STATUS current
			DESCRIPTION
				"RX packets UDP source port"
		::= { ipa2000c01v1Entry 309 }

		-- 1.3.6.1.4.1.10106.3.101291.1.1.311
		ipa2000c01v1Rx2LParam OBJECT-TYPE
			SYNTAX Uint5
			MAX-ACCESS read-only
			STATUS current
			DESCRIPTION
				"L parameter (FEC mode columns)"
		::= { ipa2000c01v1Entry 311 }

		-- 1.3.6.1.4.1.10106.3.101291.1.1.313
		ipa2000c01v1Rx2FecMode OBJECT-TYPE
			SYNTAX FecMode
			MAX-ACCESS read-only
			STATUS current
			DESCRIPTION
				"Protocol"
		::= { ipa2000c01v1Entry 313 }

		-- 1.3.6.1.4.1.10106.3.101291.1.1.315
		ipa2000c01v1Rx2PacketSize OBJECT-TYPE
			SYNTAX Bit02041188
			MAX-ACCESS read-only
			STATUS current
			DESCRIPTION
				"Bytes in TS packets"
		::= { ipa2000c01v1Entry 315 }

		-- 1.3.6.1.4.1.10106.3.101291.1.1.317
		ipa2000c01v1Rx2DParam OBJECT-TYPE
			SYNTAX Uint5
			MAX-ACCESS read-only
			STATUS current
			DESCRIPTION
				"D parameter (FEC mode rows)"
		::= { ipa2000c01v1Entry 317 }

		-- 1.3.6.1.4.1.10106.3.101291.1.1.319
		ipa2000c01v1Rx2TsPcks OBJECT-TYPE
			SYNTAX Uint3
			MAX-ACCESS read-only
			STATUS current
			DESCRIPTION
				"TS packets in each IP packet"
		::= { ipa2000c01v1Entry 319 }

		-- 1.3.6.1.4.1.10106.3.101291.1.1.321
		ipa2000c01v1Rx2PacketRate OBJECT-TYPE
			SYNTAX PacketRate
			MAX-ACCESS read-only
			STATUS current
			DESCRIPTION
				"IP packet rate"
		::= { ipa2000c01v1Entry 321 }

		-- 1.3.6.1.4.1.10106.3.101291.1.1.323
		ipa2000c01v1Rx2FecRate OBJECT-TYPE
			SYNTAX PacketRate
			MAX-ACCESS read-only
			STATUS current
			DESCRIPTION
				"FEC packet rate"
		::= { ipa2000c01v1Entry 323 }

		-- 1.3.6.1.4.1.10106.3.101291.1.1.325
		ipa2000c01v1Rx2TimeRst OBJECT-TYPE
			SYNTAX TimeS4
			MAX-ACCESS read-only
			STATUS current
			DESCRIPTION
				"Elapsed time since last reset"
		::= { ipa2000c01v1Entry 325 }

		-- 1.3.6.1.4.1.10106.3.101291.1.1.327
		ipa2000c01v1Rx2LostIpPck OBJECT-TYPE
			SYNTAX Uint16
			MAX-ACCESS read-only
			STATUS current
			DESCRIPTION
				"Lost IP packets"
		::= { ipa2000c01v1Entry 327 }

		-- 1.3.6.1.4.1.10106.3.101291.1.1.329
		ipa2000c01v1Rx2RecIpPck OBJECT-TYPE
			SYNTAX Uint16
			MAX-ACCESS read-only
			STATUS current
			DESCRIPTION
				"Recovered IP packets"
		::= { ipa2000c01v1Entry 329 }

		-- 1.3.6.1.4.1.10106.3.101291.1.1.331
		ipa2000c01v1Rx2OutOrdPck OBJECT-TYPE
			SYNTAX Uint16
			MAX-ACCESS read-only
			STATUS current
			DESCRIPTION
				"Out of order IP packets"
		::= { ipa2000c01v1Entry 331 }

		-- 1.3.6.1.4.1.10106.3.101291.1.1.333
		ipa2000c01v1Rx2BufferStat OBJECT-TYPE
			SYNTAX Rate1
			MAX-ACCESS read-only
			STATUS current
			DESCRIPTION
				"Buffer filling status in non DVB-T mode (with respecto to the central value)"
		::= { ipa2000c01v1Entry 333 }

		-- 1.3.6.1.4.1.10106.3.101291.1.1.335
		ipa2000c01v1LocalIpAdd3 OBJECT-TYPE
			SYNTAX Uint8
			MAX-ACCESS read-write
			STATUS current
			DESCRIPTION
				"IP address (3)"
		::= { ipa2000c01v1Entry 335 }

		-- 1.3.6.1.4.1.10106.3.101291.1.1.337
		ipa2000c01v1LocalIpAdd2 OBJECT-TYPE
			SYNTAX Uint8
			MAX-ACCESS read-write
			STATUS current
			DESCRIPTION
				"IP address (2)"
		::= { ipa2000c01v1Entry 337 }

		-- 1.3.6.1.4.1.10106.3.101291.1.1.339
		ipa2000c01v1LocalIpAdd1 OBJECT-TYPE
			SYNTAX Uint8
			MAX-ACCESS read-write
			STATUS current
			DESCRIPTION
				"IP address (1)"
		::= { ipa2000c01v1Entry 339 }

		-- 1.3.6.1.4.1.10106.3.101291.1.1.341
		ipa2000c01v1LocalIpAdd0 OBJECT-TYPE
			SYNTAX Uint8
			MAX-ACCESS read-write
			STATUS current
			DESCRIPTION
				"IP address (0)"
		::= { ipa2000c01v1Entry 341 }

		-- 1.3.6.1.4.1.10106.3.101291.1.1.343
		ipa2000c01v1LocalIpMask3 OBJECT-TYPE
			SYNTAX Uint8
			MAX-ACCESS read-write
			STATUS current
			DESCRIPTION
				"IP mask (3)"
		::= { ipa2000c01v1Entry 343 }

		-- 1.3.6.1.4.1.10106.3.101291.1.1.345
		ipa2000c01v1LocalIpMask2 OBJECT-TYPE
			SYNTAX Uint8
			MAX-ACCESS read-write
			STATUS current
			DESCRIPTION
				"IP mask (2)"
		::= { ipa2000c01v1Entry 345 }

		-- 1.3.6.1.4.1.10106.3.101291.1.1.347
		ipa2000c01v1LocalIpMask1 OBJECT-TYPE
			SYNTAX Uint8
			MAX-ACCESS read-write
			STATUS current
			DESCRIPTION
				"IP mask (1)"
		::= { ipa2000c01v1Entry 347 }

		-- 1.3.6.1.4.1.10106.3.101291.1.1.349
		ipa2000c01v1LocalIpMask0 OBJECT-TYPE
			SYNTAX Uint8
			MAX-ACCESS read-write
			STATUS current
			DESCRIPTION
				"IP mask (0)"
		::= { ipa2000c01v1Entry 349 }

		-- 1.3.6.1.4.1.10106.3.101291.1.1.351
		ipa2000c01v1LocalIp2Add3 OBJECT-TYPE
			SYNTAX Uint8
			MAX-ACCESS read-write
			STATUS current
			DESCRIPTION
				"IP address (3)"
		::= { ipa2000c01v1Entry 351 }

		-- 1.3.6.1.4.1.10106.3.101291.1.1.353
		ipa2000c01v1LocalIp2Add2 OBJECT-TYPE
			SYNTAX Uint8
			MAX-ACCESS read-write
			STATUS current
			DESCRIPTION
				"IP address (2)"
		::= { ipa2000c01v1Entry 353 }

		-- 1.3.6.1.4.1.10106.3.101291.1.1.355
		ipa2000c01v1LocalIp2Add1 OBJECT-TYPE
			SYNTAX Uint8
			MAX-ACCESS read-write
			STATUS current
			DESCRIPTION
				"IP address (1)"
		::= { ipa2000c01v1Entry 355 }

		-- 1.3.6.1.4.1.10106.3.101291.1.1.357
		ipa2000c01v1LocalIp2Add0 OBJECT-TYPE
			SYNTAX Uint8
			MAX-ACCESS read-write
			STATUS current
			DESCRIPTION
				"IP address (0)"
		::= { ipa2000c01v1Entry 357 }

		-- 1.3.6.1.4.1.10106.3.101291.1.1.359
		ipa2000c01v1LocalIp2Msk3 OBJECT-TYPE
			SYNTAX Uint8
			MAX-ACCESS read-write
			STATUS current
			DESCRIPTION
				"IP mask (3)"
		::= { ipa2000c01v1Entry 359 }

		-- 1.3.6.1.4.1.10106.3.101291.1.1.361
		ipa2000c01v1LocalIp2Msk2 OBJECT-TYPE
			SYNTAX Uint8
			MAX-ACCESS read-write
			STATUS current
			DESCRIPTION
				"IP mask (2)"
		::= { ipa2000c01v1Entry 361 }

		-- 1.3.6.1.4.1.10106.3.101291.1.1.363
		ipa2000c01v1LocalIp2Msk1 OBJECT-TYPE
			SYNTAX Uint8
			MAX-ACCESS read-write
			STATUS current
			DESCRIPTION
				"IP mask (1)"
		::= { ipa2000c01v1Entry 363 }

		-- 1.3.6.1.4.1.10106.3.101291.1.1.365
		ipa2000c01v1LocalIp2Msk0 OBJECT-TYPE
			SYNTAX Uint8
			MAX-ACCESS read-write
			STATUS current
			DESCRIPTION
				"IP mask (0)"
		::= { ipa2000c01v1Entry 365 }

		-- 1.3.6.1.4.1.10106.3.101291.1.1.367
		ipa2000c01v1LocalIpGway3 OBJECT-TYPE
			SYNTAX Uint8
			MAX-ACCESS read-write
			STATUS current
			DESCRIPTION
				"Gateway IP address (3)"
		::= { ipa2000c01v1Entry 367 }

		-- 1.3.6.1.4.1.10106.3.101291.1.1.369
		ipa2000c01v1LocalIpGway2 OBJECT-TYPE
			SYNTAX Uint8
			MAX-ACCESS read-write
			STATUS current
			DESCRIPTION
				"Gateway IP address (2)"
		::= { ipa2000c01v1Entry 369 }

		-- 1.3.6.1.4.1.10106.3.101291.1.1.371
		ipa2000c01v1LocalIpGway1 OBJECT-TYPE
			SYNTAX Uint8
			MAX-ACCESS read-write
			STATUS current
			DESCRIPTION
				"Gateway IP address (1)"
		::= { ipa2000c01v1Entry 371 }

		-- 1.3.6.1.4.1.10106.3.101291.1.1.373
		ipa2000c01v1LocalIpGway0 OBJECT-TYPE
			SYNTAX Uint8
			MAX-ACCESS read-write
			STATUS current
			DESCRIPTION
				"Gateway IP address (0)"
		::= { ipa2000c01v1Entry 373 }

		-- 1.3.6.1.4.1.10106.3.101291.1.1.375
		ipa2000c01v1SysError OBJECT-TYPE
			SYNTAX SysError0
			MAX-ACCESS read-only
			STATUS current
			DESCRIPTION
				"System error. (Irrecoverable alarm or event)"
		::= { ipa2000c01v1Entry 375 }

		-- 1.3.6.1.4.1.10106.3.101291.1.1.377
		ipa2000c01v1Link1 OBJECT-TYPE
			SYNTAX Ipa2EtherStat
			MAX-ACCESS read-only
			STATUS current
			DESCRIPTION
				"Ethernet conection status"
		::= { ipa2000c01v1Entry 377 }

		-- 1.3.6.1.4.1.10106.3.101291.1.1.378
		ipa2000c01v1Link1TrapEnable OBJECT-TYPE
			SYNTAX AlarmEnable
			MAX-ACCESS read-write
			STATUS current
			DESCRIPTION
				"Ethernet conection status Trap Enable"
		::= { ipa2000c01v1Entry 378 }

		-- 1.3.6.1.4.1.10106.3.101291.1.1.379
		ipa2000c01v1System1 OBJECT-TYPE
			SYNTAX Ipa2EtherSys
			MAX-ACCESS read-only
			STATUS current
			DESCRIPTION
				"Ethernet conection system"
		::= { ipa2000c01v1Entry 379 }

		-- 1.3.6.1.4.1.10106.3.101291.1.1.380
		ipa2000c01v1System1TrapEnable OBJECT-TYPE
			SYNTAX AlarmEnable
			MAX-ACCESS read-write
			STATUS current
			DESCRIPTION
				"Ethernet conection system Trap Enable"
		::= { ipa2000c01v1Entry 380 }

		-- 1.3.6.1.4.1.10106.3.101291.1.1.381
		ipa2000c01v1Link2 OBJECT-TYPE
			SYNTAX Ipa2EtherStat
			MAX-ACCESS read-only
			STATUS current
			DESCRIPTION
				"Ethernet conection status"
		::= { ipa2000c01v1Entry 381 }

		-- 1.3.6.1.4.1.10106.3.101291.1.1.382
		ipa2000c01v1Link2TrapEnable OBJECT-TYPE
			SYNTAX AlarmEnable
			MAX-ACCESS read-write
			STATUS current
			DESCRIPTION
				"Ethernet conection status Trap Enable"
		::= { ipa2000c01v1Entry 382 }

		-- 1.3.6.1.4.1.10106.3.101291.1.1.383
		ipa2000c01v1System2 OBJECT-TYPE
			SYNTAX Ipa2EtherSys
			MAX-ACCESS read-only
			STATUS current
			DESCRIPTION
				"Ethernet conection system"
		::= { ipa2000c01v1Entry 383 }

		-- 1.3.6.1.4.1.10106.3.101291.1.1.384
		ipa2000c01v1System2TrapEnable OBJECT-TYPE
			SYNTAX AlarmEnable
			MAX-ACCESS read-write
			STATUS current
			DESCRIPTION
				"Ethernet conection system Trap Enable"
		::= { ipa2000c01v1Entry 384 }

		-- 1.3.6.1.4.1.10106.3.101291.1.1.385
		ipa2000c01v11ppsFail OBJECT-TYPE
			SYNTAX BitFail
			MAX-ACCESS read-only
			STATUS current
			DESCRIPTION
				"1PPS reference input status"
		::= { ipa2000c01v1Entry 385 }

		-- 1.3.6.1.4.1.10106.3.101291.1.1.386
		ipa2000c01v11ppsFailTrapEnable OBJECT-TYPE
			SYNTAX AlarmEnable
			MAX-ACCESS read-write
			STATUS current
			DESCRIPTION
				"1PPS reference input status Trap Enable"
		::= { ipa2000c01v1Entry 386 }

		-- 1.3.6.1.4.1.10106.3.101291.1.1.387
		ipa2000c01v113mhzFail OBJECT-TYPE
			SYNTAX BitFail
			MAX-ACCESS read-only
			STATUS current
			DESCRIPTION
				"13.5 MHz internal backplane reference input status"
		::= { ipa2000c01v1Entry 387 }

		-- 1.3.6.1.4.1.10106.3.101291.1.1.388
		ipa2000c01v113mhzFailTrapEnable OBJECT-TYPE
			SYNTAX AlarmEnable
			MAX-ACCESS read-write
			STATUS current
			DESCRIPTION
				"13.5 MHz internal backplane reference input status Trap Enable"
		::= { ipa2000c01v1Entry 388 }

		-- 1.3.6.1.4.1.10106.3.101291.1.1.389
		ipa2000c01v1OutputFail OBJECT-TYPE
			SYNTAX BitFail
			MAX-ACCESS read-only
			STATUS current
			DESCRIPTION
				"The output signal is not valid because all inputs failed"
		::= { ipa2000c01v1Entry 389 }

		-- 1.3.6.1.4.1.10106.3.101291.1.1.390
		ipa2000c01v1OutputFailTrapEnable OBJECT-TYPE
			SYNTAX AlarmEnable
			MAX-ACCESS read-write
			STATUS current
			DESCRIPTION
				"The output signal is not valid because all inputs failed Trap Enable"
		::= { ipa2000c01v1Entry 390 }

		-- 1.3.6.1.4.1.10106.3.101291.1.1.391
		ipa2000c01v1InputStChange OBJECT-TYPE
			SYNTAX BitFail
			MAX-ACCESS read-only
			STATUS current
			DESCRIPTION
				"Signals a change in input status"
		::= { ipa2000c01v1Entry 391 }

		-- 1.3.6.1.4.1.10106.3.101291.1.1.393
		ipa2000c01v1InputChange OBJECT-TYPE
			SYNTAX BitFail
			MAX-ACCESS read-only
			STATUS current
			DESCRIPTION
				"Signals a change in selected input"
		::= { ipa2000c01v1Entry 393 }

		-- 1.3.6.1.4.1.10106.3.101291.1.1.395
		ipa2000c01v1SyncLossErr1 OBJECT-TYPE
			SYNTAX BitFail
			MAX-ACCESS read-only
			STATUS current
			DESCRIPTION
				"Sync loss fail (Fist priority  parameter 1.1)"
		::= { ipa2000c01v1Entry 395 }

		-- 1.3.6.1.4.1.10106.3.101291.1.1.396
		ipa2000c01v1SyncLossErr1TrapEnable OBJECT-TYPE
			SYNTAX AlarmEnable
			MAX-ACCESS read-write
			STATUS current
			DESCRIPTION
				"Sync loss fail (Fist priority  parameter 1.1) Trap Enable"
		::= { ipa2000c01v1Entry 396 }

		-- 1.3.6.1.4.1.10106.3.101291.1.1.397
		ipa2000c01v1SyncByteErr1 OBJECT-TYPE
			SYNTAX BitFail
			MAX-ACCESS read-only
			STATUS current
			DESCRIPTION
				"Sync byte error (Fist priority  parameter 1.2)"
		::= { ipa2000c01v1Entry 397 }

		-- 1.3.6.1.4.1.10106.3.101291.1.1.398
		ipa2000c01v1SyncByteErr1TrapEnable OBJECT-TYPE
			SYNTAX AlarmEnable
			MAX-ACCESS read-write
			STATUS current
			DESCRIPTION
				"Sync byte error (Fist priority  parameter 1.2) Trap Enable"
		::= { ipa2000c01v1Entry 398 }

		-- 1.3.6.1.4.1.10106.3.101291.1.1.399
		ipa2000c01v1PatError1 OBJECT-TYPE
			SYNTAX BitFail
			MAX-ACCESS read-only
			STATUS current
			DESCRIPTION
				"PAT error (Fist priority  parameter 1.3)"
		::= { ipa2000c01v1Entry 399 }

		-- 1.3.6.1.4.1.10106.3.101291.1.1.400
		ipa2000c01v1PatError1TrapEnable OBJECT-TYPE
			SYNTAX AlarmEnable
			MAX-ACCESS read-write
			STATUS current
			DESCRIPTION
				"PAT error (Fist priority  parameter 1.3) Trap Enable"
		::= { ipa2000c01v1Entry 400 }

		-- 1.3.6.1.4.1.10106.3.101291.1.1.401
		ipa2000c01v1CcError1 OBJECT-TYPE
			SYNTAX BitFail
			MAX-ACCESS read-only
			STATUS current
			DESCRIPTION
				"Continuity counter error (Fist priority  parameter 1.4)"
		::= { ipa2000c01v1Entry 401 }

		-- 1.3.6.1.4.1.10106.3.101291.1.1.402
		ipa2000c01v1CcError1TrapEnable OBJECT-TYPE
			SYNTAX AlarmEnable
			MAX-ACCESS read-write
			STATUS current
			DESCRIPTION
				"Continuity counter error (Fist priority  parameter 1.4) Trap Enable"
		::= { ipa2000c01v1Entry 402 }

		-- 1.3.6.1.4.1.10106.3.101291.1.1.403
		ipa2000c01v1PmtError1 OBJECT-TYPE
			SYNTAX BitFail
			MAX-ACCESS read-only
			STATUS current
			DESCRIPTION
				"PMT error (Fist priority  parameter 1.5)"
		::= { ipa2000c01v1Entry 403 }

		-- 1.3.6.1.4.1.10106.3.101291.1.1.404
		ipa2000c01v1PmtError1TrapEnable OBJECT-TYPE
			SYNTAX AlarmEnable
			MAX-ACCESS read-write
			STATUS current
			DESCRIPTION
				"PMT error (Fist priority  parameter 1.5) Trap Enable"
		::= { ipa2000c01v1Entry 404 }

		-- 1.3.6.1.4.1.10106.3.101291.1.1.405
		ipa2000c01v1PidError1 OBJECT-TYPE
			SYNTAX BitFail
			MAX-ACCESS read-only
			STATUS current
			DESCRIPTION
				"PID error (Fist priority  parameter 1.6)"
		::= { ipa2000c01v1Entry 405 }

		-- 1.3.6.1.4.1.10106.3.101291.1.1.406
		ipa2000c01v1PidError1TrapEnable OBJECT-TYPE
			SYNTAX AlarmEnable
			MAX-ACCESS read-write
			STATUS current
			DESCRIPTION
				"PID error (Fist priority  parameter 1.6) Trap Enable"
		::= { ipa2000c01v1Entry 406 }

		-- 1.3.6.1.4.1.10106.3.101291.1.1.407
		ipa2000c01v1MipError1 OBJECT-TYPE
			SYNTAX BitFail
			MAX-ACCESS read-only
			STATUS current
			DESCRIPTION
				"MIP error. DVB-T compliant"
		::= { ipa2000c01v1Entry 407 }

		-- 1.3.6.1.4.1.10106.3.101291.1.1.408
		ipa2000c01v1MipError1TrapEnable OBJECT-TYPE
			SYNTAX AlarmEnable
			MAX-ACCESS read-write
			STATUS current
			DESCRIPTION
				"MIP error. DVB-T compliant Trap Enable"
		::= { ipa2000c01v1Entry 408 }

		-- 1.3.6.1.4.1.10106.3.101291.1.1.409
		ipa2000c01v1GlobalError1 OBJECT-TYPE
			SYNTAX BitFail
			MAX-ACCESS read-only
			STATUS current
			DESCRIPTION
				"Global fail"
		::= { ipa2000c01v1Entry 409 }

		-- 1.3.6.1.4.1.10106.3.101291.1.1.410
		ipa2000c01v1GlobalError1TrapEnable OBJECT-TYPE
			SYNTAX AlarmEnable
			MAX-ACCESS read-write
			STATUS current
			DESCRIPTION
				"Global fail Trap Enable"
		::= { ipa2000c01v1Entry 410 }

		-- 1.3.6.1.4.1.10106.3.101291.1.1.411
		ipa2000c01v1SyncLossErr2 OBJECT-TYPE
			SYNTAX BitFail
			MAX-ACCESS read-only
			STATUS current
			DESCRIPTION
				"Sync loss fail (Fist priority  parameter 1.1)"
		::= { ipa2000c01v1Entry 411 }

		-- 1.3.6.1.4.1.10106.3.101291.1.1.412
		ipa2000c01v1SyncLossErr2TrapEnable OBJECT-TYPE
			SYNTAX AlarmEnable
			MAX-ACCESS read-write
			STATUS current
			DESCRIPTION
				"Sync loss fail (Fist priority  parameter 1.1) Trap Enable"
		::= { ipa2000c01v1Entry 412 }

		-- 1.3.6.1.4.1.10106.3.101291.1.1.413
		ipa2000c01v1SyncByteErr2 OBJECT-TYPE
			SYNTAX BitFail
			MAX-ACCESS read-only
			STATUS current
			DESCRIPTION
				"Sync byte error (Fist priority  parameter 1.2)"
		::= { ipa2000c01v1Entry 413 }

		-- 1.3.6.1.4.1.10106.3.101291.1.1.414
		ipa2000c01v1SyncByteErr2TrapEnable OBJECT-TYPE
			SYNTAX AlarmEnable
			MAX-ACCESS read-write
			STATUS current
			DESCRIPTION
				"Sync byte error (Fist priority  parameter 1.2) Trap Enable"
		::= { ipa2000c01v1Entry 414 }

		-- 1.3.6.1.4.1.10106.3.101291.1.1.415
		ipa2000c01v1PatError2 OBJECT-TYPE
			SYNTAX BitFail
			MAX-ACCESS read-only
			STATUS current
			DESCRIPTION
				"PAT error (Fist priority  parameter 1.3)"
		::= { ipa2000c01v1Entry 415 }

		-- 1.3.6.1.4.1.10106.3.101291.1.1.416
		ipa2000c01v1PatError2TrapEnable OBJECT-TYPE
			SYNTAX AlarmEnable
			MAX-ACCESS read-write
			STATUS current
			DESCRIPTION
				"PAT error (Fist priority  parameter 1.3) Trap Enable"
		::= { ipa2000c01v1Entry 416 }

		-- 1.3.6.1.4.1.10106.3.101291.1.1.417
		ipa2000c01v1CcError2 OBJECT-TYPE
			SYNTAX BitFail
			MAX-ACCESS read-only
			STATUS current
			DESCRIPTION
				"Continuity counter error (Fist priority  parameter 1.4)"
		::= { ipa2000c01v1Entry 417 }

		-- 1.3.6.1.4.1.10106.3.101291.1.1.418
		ipa2000c01v1CcError2TrapEnable OBJECT-TYPE
			SYNTAX AlarmEnable
			MAX-ACCESS read-write
			STATUS current
			DESCRIPTION
				"Continuity counter error (Fist priority  parameter 1.4) Trap Enable"
		::= { ipa2000c01v1Entry 418 }

		-- 1.3.6.1.4.1.10106.3.101291.1.1.419
		ipa2000c01v1PmtError2 OBJECT-TYPE
			SYNTAX BitFail
			MAX-ACCESS read-only
			STATUS current
			DESCRIPTION
				"PMT error (Fist priority  parameter 1.5)"
		::= { ipa2000c01v1Entry 419 }

		-- 1.3.6.1.4.1.10106.3.101291.1.1.420
		ipa2000c01v1PmtError2TrapEnable OBJECT-TYPE
			SYNTAX AlarmEnable
			MAX-ACCESS read-write
			STATUS current
			DESCRIPTION
				"PMT error (Fist priority  parameter 1.5) Trap Enable"
		::= { ipa2000c01v1Entry 420 }

		-- 1.3.6.1.4.1.10106.3.101291.1.1.421
		ipa2000c01v1PidError2 OBJECT-TYPE
			SYNTAX BitFail
			MAX-ACCESS read-only
			STATUS current
			DESCRIPTION
				"PID error (Fist priority  parameter 1.6)"
		::= { ipa2000c01v1Entry 421 }

		-- 1.3.6.1.4.1.10106.3.101291.1.1.422
		ipa2000c01v1PidError2TrapEnable OBJECT-TYPE
			SYNTAX AlarmEnable
			MAX-ACCESS read-write
			STATUS current
			DESCRIPTION
				"PID error (Fist priority  parameter 1.6) Trap Enable"
		::= { ipa2000c01v1Entry 422 }

		-- 1.3.6.1.4.1.10106.3.101291.1.1.423
		ipa2000c01v1MipError2 OBJECT-TYPE
			SYNTAX BitFail
			MAX-ACCESS read-only
			STATUS current
			DESCRIPTION
				"MIP error. DVB-T compliant"
		::= { ipa2000c01v1Entry 423 }

		-- 1.3.6.1.4.1.10106.3.101291.1.1.424
		ipa2000c01v1MipError2TrapEnable OBJECT-TYPE
			SYNTAX AlarmEnable
			MAX-ACCESS read-write
			STATUS current
			DESCRIPTION
				"MIP error. DVB-T compliant Trap Enable"
		::= { ipa2000c01v1Entry 424 }

		-- 1.3.6.1.4.1.10106.3.101291.1.1.425
		ipa2000c01v1GlobalError2 OBJECT-TYPE
			SYNTAX BitFail
			MAX-ACCESS read-only
			STATUS current
			DESCRIPTION
				"Global fail"
		::= { ipa2000c01v1Entry 425 }

		-- 1.3.6.1.4.1.10106.3.101291.1.1.426
		ipa2000c01v1GlobalError2TrapEnable OBJECT-TYPE
			SYNTAX AlarmEnable
			MAX-ACCESS read-write
			STATUS current
			DESCRIPTION
				"Global fail Trap Enable"
		::= { ipa2000c01v1Entry 426 }

		-- 1.3.6.1.4.1.10106.3.101291.1.1.427
		ipa2000c01v1Ch1DelWar OBJECT-TYPE
			SYNTAX BitFail
			MAX-ACCESS read-only
			STATUS current
			DESCRIPTION
				"The delay is greater than the programmed output delay"
		::= { ipa2000c01v1Entry 427 }

		-- 1.3.6.1.4.1.10106.3.101291.1.1.428
		ipa2000c01v1Ch1DelWarTrapEnable OBJECT-TYPE
			SYNTAX AlarmEnable
			MAX-ACCESS read-write
			STATUS current
			DESCRIPTION
				"The delay is greater than the programmed output delay Trap Enable"
		::= { ipa2000c01v1Entry 428 }

		-- 1.3.6.1.4.1.10106.3.101291.1.1.429
		ipa2000c01v1Ch2DelWar OBJECT-TYPE
			SYNTAX BitFail
			MAX-ACCESS read-only
			STATUS current
			DESCRIPTION
				"The channel 2 delay is greater than the programmed output delay"
		::= { ipa2000c01v1Entry 429 }

		-- 1.3.6.1.4.1.10106.3.101291.1.1.430
		ipa2000c01v1Ch2DelWarTrapEnable OBJECT-TYPE
			SYNTAX AlarmEnable
			MAX-ACCESS read-write
			STATUS current
			DESCRIPTION
				"The channel 2 delay is greater than the programmed output delay Trap Enable"
		::= { ipa2000c01v1Entry 430 }

		-- 1.3.6.1.4.1.10106.3.101291.1.1.431
		ipa2000c01v1GlobalSeam OBJECT-TYPE
			SYNTAX Bit0Sea1Nse
			MAX-ACCESS read-only
			STATUS current
			DESCRIPTION
				"Global seamles switching capability"
		::= { ipa2000c01v1Entry 431 }

		-- 1.3.6.1.4.1.10106.3.101291.1.1.432
		ipa2000c01v1GlobalSeamTrapEnable OBJECT-TYPE
			SYNTAX AlarmEnable
			MAX-ACCESS read-write
			STATUS current
			DESCRIPTION
				"Global seamles switching capability Trap Enable"
		::= { ipa2000c01v1Entry 432 }

		-- 1.3.6.1.4.1.10106.3.101291.1.1.433
		ipa2000c01v1Channel1Delay OBJECT-TYPE
			SYNTAX DelayX1004bNs
			MAX-ACCESS read-only
			STATUS current
			DESCRIPTION
				"DVB-T mode: input delay refered to 1PPS reference"
		::= { ipa2000c01v1Entry 433 }

		-- 1.3.6.1.4.1.10106.3.101291.1.1.435
		ipa2000c01v1Channel2Delay OBJECT-TYPE
			SYNTAX DelayX1004bNs
			MAX-ACCESS read-only
			STATUS current
			DESCRIPTION
				"DVB-T mode: input delay refered to 1PPS reference"
		::= { ipa2000c01v1Entry 435 }

		-- 1.3.6.1.4.1.10106.3.101291.1.1.437
		ipa2000c01v1ArpValid1 OBJECT-TYPE
			SYNTAX BitFailN
			MAX-ACCESS read-only
			STATUS current
			DESCRIPTION
				"Valid ARP response (Unicast mode)"
		::= { ipa2000c01v1Entry 437 }

		-- 1.3.6.1.4.1.10106.3.101291.1.1.439
		ipa2000c01v1IcmpError1 OBJECT-TYPE
			SYNTAX BitFail
			MAX-ACCESS read-only
			STATUS current
			DESCRIPTION
				"Destination unreachable (ICMP destination unrechable packets received)"
		::= { ipa2000c01v1Entry 439 }

		-- 1.3.6.1.4.1.10106.3.101291.1.1.441
		ipa2000c01v1ArpValid2 OBJECT-TYPE
			SYNTAX BitFailN
			MAX-ACCESS read-only
			STATUS current
			DESCRIPTION
				"Valid ARP response (Unicast mode)"
		::= { ipa2000c01v1Entry 441 }

		-- 1.3.6.1.4.1.10106.3.101291.1.1.443
		ipa2000c01v1IcmpError2 OBJECT-TYPE
			SYNTAX BitFail
			MAX-ACCESS read-only
			STATUS current
			DESCRIPTION
				"Destination unreachable (ICMP destination unrechable packets received)"
		::= { ipa2000c01v1Entry 443 }

		-- 1.3.6.1.4.1.10106.3.101291.1.1.445
		ipa2000c01v1SerialNo OBJECT-TYPE
			SYNTAX SerialNo
			MAX-ACCESS read-only
			STATUS current
			DESCRIPTION
				"Serial number"
		::= { ipa2000c01v1Entry 445 }

		-- 1.3.6.1.4.1.10106.3.101291.1.1.447
		ipa2000c01v1SpeedForce1 OBJECT-TYPE
			SYNTAX Bit0Ann1For
			MAX-ACCESS read-write
			STATUS current
			DESCRIPTION
				"Allows selecting if the speed/mode is forced or announced for autonegotiation"
		::= { ipa2000c01v1Entry 447 }

		-- 1.3.6.1.4.1.10106.3.101291.1.1.449
		ipa2000c01v1SpeedForce2 OBJECT-TYPE
			SYNTAX Bit0Ann1For
			MAX-ACCESS read-write
			STATUS current
			DESCRIPTION
				"Allows selecting if the speed/mode is forced or announced for autonegotiation"
		::= { ipa2000c01v1Entry 449 }

		-- 1.3.6.1.4.1.10106.3.101291.1.1.451
		ipa2000c01v1BadCrcPck1 OBJECT-TYPE
			SYNTAX Uint16
			MAX-ACCESS read-only
			STATUS current
			DESCRIPTION
				"Bad CRC packets"
		::= { ipa2000c01v1Entry 451 }

		-- 1.3.6.1.4.1.10106.3.101291.1.1.453
		ipa2000c01v1BadCrcPck2 OBJECT-TYPE
			SYNTAX Uint16
			MAX-ACCESS read-only
			STATUS current
			DESCRIPTION
				"Bad CRC packets"
		::= { ipa2000c01v1Entry 453 }

		-- 1.3.6.1.4.1.10106.3.101291.1.1.455
		ipa2000c01v1InpFailMode OBJECT-TYPE
			SYNTAX Bit0No1Yes
			MAX-ACCESS read-write
			STATUS current
			DESCRIPTION
				"Selects if the output is muted when all the inputs fail"
		::= { ipa2000c01v1Entry 455 }

		-- 1.3.6.1.4.1.10106.3.101291.1.1.457
		ipa2000c01v1PatErrorTime OBJECT-TYPE
			SYNTAX TimeX1Ms1
			MAX-ACCESS read-write
			STATUS current
			DESCRIPTION
				"PAT error time out"
		::= { ipa2000c01v1Entry 457 }

		-- 1.3.6.1.4.1.10106.3.101291.1.1.459
		ipa2000c01v1PmtErrorTime OBJECT-TYPE
			SYNTAX TimeX1Ms1
			MAX-ACCESS read-write
			STATUS current
			DESCRIPTION
				"PMT error time out"
		::= { ipa2000c01v1Entry 459 }

		-- 1.3.6.1.4.1.10106.3.101291.1.1.461
		ipa2000c01v1IpRedTx13 OBJECT-TYPE
			SYNTAX Uint8
			MAX-ACCESS read-write
			STATUS current
			DESCRIPTION
				"Redundant source IP address(3)"
		::= { ipa2000c01v1Entry 461 }

		-- 1.3.6.1.4.1.10106.3.101291.1.1.463
		ipa2000c01v1IpRedTx12 OBJECT-TYPE
			SYNTAX Uint8
			MAX-ACCESS read-write
			STATUS current
			DESCRIPTION
				"Redundant source IP address(2)"
		::= { ipa2000c01v1Entry 463 }

		-- 1.3.6.1.4.1.10106.3.101291.1.1.465
		ipa2000c01v1IpRedTx11 OBJECT-TYPE
			SYNTAX Uint8
			MAX-ACCESS read-write
			STATUS current
			DESCRIPTION
				"Redundant source IP address(1)"
		::= { ipa2000c01v1Entry 465 }

		-- 1.3.6.1.4.1.10106.3.101291.1.1.467
		ipa2000c01v1IpRedTx10 OBJECT-TYPE
			SYNTAX Uint8
			MAX-ACCESS read-write
			STATUS current
			DESCRIPTION
				"Redundant source IP address(0)"
		::= { ipa2000c01v1Entry 467 }

		-- 1.3.6.1.4.1.10106.3.101291.1.1.469
		ipa2000c01v1IpRedTx23 OBJECT-TYPE
			SYNTAX Uint8
			MAX-ACCESS read-write
			STATUS current
			DESCRIPTION
				"Redundant source IP address(3)"
		::= { ipa2000c01v1Entry 469 }

		-- 1.3.6.1.4.1.10106.3.101291.1.1.471
		ipa2000c01v1IpRedTx22 OBJECT-TYPE
			SYNTAX Uint8
			MAX-ACCESS read-write
			STATUS current
			DESCRIPTION
				"Redundant source IP address(2)"
		::= { ipa2000c01v1Entry 471 }

		-- 1.3.6.1.4.1.10106.3.101291.1.1.473
		ipa2000c01v1IpRedTx21 OBJECT-TYPE
			SYNTAX Uint8
			MAX-ACCESS read-write
			STATUS current
			DESCRIPTION
				"Redundant source IP address(1)"
		::= { ipa2000c01v1Entry 473 }

		-- 1.3.6.1.4.1.10106.3.101291.1.1.475
		ipa2000c01v1IpRedTx20 OBJECT-TYPE
			SYNTAX Uint8
			MAX-ACCESS read-write
			STATUS current
			DESCRIPTION
				"Redundant source IP address(0)"
		::= { ipa2000c01v1Entry 475 }

		-- 1.3.6.1.4.1.10106.3.101291.1.1.477
		ipa2000c01v1TxIpSrcAvai1 OBJECT-TYPE
			SYNTAX BitFailN
			MAX-ACCESS read-only
			STATUS current
			DESCRIPTION
				"Signal ready to TX"
		::= { ipa2000c01v1Entry 477 }

		-- 1.3.6.1.4.1.10106.3.101291.1.1.479
		ipa2000c01v1TxIpSrcAvai2 OBJECT-TYPE
			SYNTAX BitFailN
			MAX-ACCESS read-only
			STATUS current
			DESCRIPTION
				"Signal ready to TX"
		::= { ipa2000c01v1Entry 479 }

		-- 1.3.6.1.4.1.10106.3.101291.1.1.481
		ipa2000c01v1Channel1Pck OBJECT-TYPE
			SYNTAX PacketNum
			MAX-ACCESS read-only
			STATUS current
			DESCRIPTION
				"Used buffer"
		::= { ipa2000c01v1Entry 481 }

		-- 1.3.6.1.4.1.10106.3.101291.1.1.483
		ipa2000c01v1Channel2Pck OBJECT-TYPE
			SYNTAX PacketNum
			MAX-ACCESS read-only
			STATUS current
			DESCRIPTION
				"Used buffer"
		::= { ipa2000c01v1Entry 483 }

		-- 1.3.6.1.4.1.10106.3.101291.1.1.485
		ipa2000c01v1RouterIp13 OBJECT-TYPE
			SYNTAX Uint8
			MAX-ACCESS read-write
			STATUS current
			DESCRIPTION
				"Router dest. IP address(3)"
		::= { ipa2000c01v1Entry 485 }

		-- 1.3.6.1.4.1.10106.3.101291.1.1.487
		ipa2000c01v1RouterIp12 OBJECT-TYPE
			SYNTAX Uint8
			MAX-ACCESS read-write
			STATUS current
			DESCRIPTION
				"Router dest. IP address(2)"
		::= { ipa2000c01v1Entry 487 }

		-- 1.3.6.1.4.1.10106.3.101291.1.1.489
		ipa2000c01v1RouterIp11 OBJECT-TYPE
			SYNTAX Uint8
			MAX-ACCESS read-write
			STATUS current
			DESCRIPTION
				"Router dest. IP address(1)"
		::= { ipa2000c01v1Entry 489 }

		-- 1.3.6.1.4.1.10106.3.101291.1.1.491
		ipa2000c01v1RouterIp10 OBJECT-TYPE
			SYNTAX Uint8
			MAX-ACCESS read-write
			STATUS current
			DESCRIPTION
				"Router dest. IP address(0)"
		::= { ipa2000c01v1Entry 491 }

		-- 1.3.6.1.4.1.10106.3.101291.1.1.493
		ipa2000c01v1RouterIp23 OBJECT-TYPE
			SYNTAX Uint8
			MAX-ACCESS read-write
			STATUS current
			DESCRIPTION
				"Router dest. IP address(3)"
		::= { ipa2000c01v1Entry 493 }

		-- 1.3.6.1.4.1.10106.3.101291.1.1.495
		ipa2000c01v1RouterIp22 OBJECT-TYPE
			SYNTAX Uint8
			MAX-ACCESS read-write
			STATUS current
			DESCRIPTION
				"Router dest. IP address(2)"
		::= { ipa2000c01v1Entry 495 }

		-- 1.3.6.1.4.1.10106.3.101291.1.1.497
		ipa2000c01v1RouterIp21 OBJECT-TYPE
			SYNTAX Uint8
			MAX-ACCESS read-write
			STATUS current
			DESCRIPTION
				"Router dest. IP address(1)"
		::= { ipa2000c01v1Entry 497 }

		-- 1.3.6.1.4.1.10106.3.101291.1.1.499
		ipa2000c01v1RouterIp20 OBJECT-TYPE
			SYNTAX Uint8
			MAX-ACCESS read-write
			STATUS current
			DESCRIPTION
				"Router dest. IP address(0)"
		::= { ipa2000c01v1Entry 499 }

		-- 1.3.6.1.4.1.10106.3.467901
		tle2001c02v1 OBJECT IDENTIFIER ::= { albalaProducts 467901 }

		-- 1.3.6.1.4.1.10106.3.467901.1
		tle2001c02v1Table  OBJECT-TYPE
			SYNTAX SEQUENCE OF Tle2001c02v1Entry
			MAX-ACCESS not-accessible
			STATUS current
			DESCRIPTION
				"Module  TLE2001C02V1 Table"
			::= { tle2001c02v1 1 }

		-- 1.3.6.1.4.1.10106.3.467901.1.1
		tle2001c02v1Entry  OBJECT-TYPE
			SYNTAX Tle2001c02v1Entry
			MAX-ACCESS not-accessible
			STATUS current
			DESCRIPTION
				"Module TLE2001C02V1 Entry"
			INDEX { tle2001c02v1Index }
			::= { tle2001c02v1Table 1 }

			Tle2001c02v1Entry ::=
			SEQUENCE {
				tle2001c02v1Index
				ModuleIndex,
				tle2001c02v1Gpo1
				Bit0Ina1Act,
				tle2001c02v1Gpo2
				Bit0Ina1Act,
				tle2001c02v1Gpo3
				Bit0Ina1Act,
				tle2001c02v1Gpo4
				Bit0Ina1Act,
				tle2001c02v1InvertGpi1Pol
				Bit0No1Yes,
				tle2001c02v1InvertGpi2Pol
				Bit0No1Yes,
				tle2001c02v1InvertGpi3Pol
				Bit0No1Yes,
				tle2001c02v1InvertGpi4Pol
				Bit0No1Yes,
				tle2001c02v1InvertGpo1Pol
				Bit0No1Yes,
				tle2001c02v1InvertGpo2Pol
				Bit0No1Yes,
				tle2001c02v1InvertGpo3Pol
				Bit0No1Yes,
				tle2001c02v1InvertGpo4Pol
				Bit0No1Yes,
				tle2001c02v1Gpi1
				Bit0Ina1Act,
				tle2001c02v1Gpi1TrapEnable
				AlarmEnable,
				tle2001c02v1Gpi2
				Bit0Ina1Act,
				tle2001c02v1Gpi2TrapEnable
				AlarmEnable,
				tle2001c02v1Gpi3
				Bit0Ina1Act,
				tle2001c02v1Gpi3TrapEnable
				AlarmEnable,
				tle2001c02v1Gpi4
				Bit0Ina1Act,
				tle2001c02v1Gpi4TrapEnable
				AlarmEnable,
				tle2001c02v1RedBoard
				Bit0No1Yes,
				tle2001c02v1RedBoardTrapEnable
				AlarmEnable,
				tle2001c02v1EthLink
				Bit0No1Yes,
				tle2001c02v1EthLinkTrapEnable
				AlarmEnable,
				tle2001c02v1EthRedAct
				Bit0No1Yes,
				tle2001c02v1EthRedActTrapEnable
				AlarmEnable,
				tle2001c02v1SerialNo
				SerialNo
			 }

		-- 1.3.6.1.4.1.10106.3.101291.1.1.1
		tle2001c02v1Index OBJECT-TYPE
			SYNTAX ModuleIndex
			MAX-ACCESS read-only
			STATUS current
			DESCRIPTION
				"Index of TLE2001C02V1 Table"
		::= { tle2001c02v1Entry 1 }

		-- 1.3.6.1.4.1.10106.3.101291.1.1.3
		tle2001c02v1Gpo1 OBJECT-TYPE
			SYNTAX Bit0Ina1Act
			MAX-ACCESS read-write
			STATUS current
			DESCRIPTION
				"Allows control of GPO1"
		::= { tle2001c02v1Entry 3 }

		-- 1.3.6.1.4.1.10106.3.101291.1.1.5
		tle2001c02v1Gpo2 OBJECT-TYPE
			SYNTAX Bit0Ina1Act
			MAX-ACCESS read-write
			STATUS current
			DESCRIPTION
				"Allows control of GPO2"
		::= { tle2001c02v1Entry 5 }

		-- 1.3.6.1.4.1.10106.3.101291.1.1.7
		tle2001c02v1Gpo3 OBJECT-TYPE
			SYNTAX Bit0Ina1Act
			MAX-ACCESS read-write
			STATUS current
			DESCRIPTION
				"Allows control of GPO3"
		::= { tle2001c02v1Entry 7 }

		-- 1.3.6.1.4.1.10106.3.101291.1.1.9
		tle2001c02v1Gpo4 OBJECT-TYPE
			SYNTAX Bit0Ina1Act
			MAX-ACCESS read-write
			STATUS current
			DESCRIPTION
				"Allows control of GPO4"
		::= { tle2001c02v1Entry 9 }

		-- 1.3.6.1.4.1.10106.3.101291.1.1.11
		tle2001c02v1InvertGpi1Pol OBJECT-TYPE
			SYNTAX Bit0No1Yes
			MAX-ACCESS read-write
			STATUS current
			DESCRIPTION
				"Changes GPI1 polarity to normally closed"
		::= { tle2001c02v1Entry 11 }

		-- 1.3.6.1.4.1.10106.3.101291.1.1.13
		tle2001c02v1InvertGpi2Pol OBJECT-TYPE
			SYNTAX Bit0No1Yes
			MAX-ACCESS read-write
			STATUS current
			DESCRIPTION
				"Changes GPI2 polarity to normally closed"
		::= { tle2001c02v1Entry 13 }

		-- 1.3.6.1.4.1.10106.3.101291.1.1.15
		tle2001c02v1InvertGpi3Pol OBJECT-TYPE
			SYNTAX Bit0No1Yes
			MAX-ACCESS read-write
			STATUS current
			DESCRIPTION
				"Changes GPI3 polarity to normally closed"
		::= { tle2001c02v1Entry 15 }

		-- 1.3.6.1.4.1.10106.3.101291.1.1.17
		tle2001c02v1InvertGpi4Pol OBJECT-TYPE
			SYNTAX Bit0No1Yes
			MAX-ACCESS read-write
			STATUS current
			DESCRIPTION
				"Changes GPI4 polarity to normally closed"
		::= { tle2001c02v1Entry 17 }

		-- 1.3.6.1.4.1.10106.3.101291.1.1.19
		tle2001c02v1InvertGpo1Pol OBJECT-TYPE
			SYNTAX Bit0No1Yes
			MAX-ACCESS read-write
			STATUS current
			DESCRIPTION
				"Allows inverting GPO1 polarity"
		::= { tle2001c02v1Entry 19 }

		-- 1.3.6.1.4.1.10106.3.101291.1.1.21
		tle2001c02v1InvertGpo2Pol OBJECT-TYPE
			SYNTAX Bit0No1Yes
			MAX-ACCESS read-write
			STATUS current
			DESCRIPTION
				"Allows inverting GPO2 polarity"
		::= { tle2001c02v1Entry 21 }

		-- 1.3.6.1.4.1.10106.3.101291.1.1.23
		tle2001c02v1InvertGpo3Pol OBJECT-TYPE
			SYNTAX Bit0No1Yes
			MAX-ACCESS read-write
			STATUS current
			DESCRIPTION
				"Allows inverting GPO3 polarity"
		::= { tle2001c02v1Entry 23 }

		-- 1.3.6.1.4.1.10106.3.101291.1.1.25
		tle2001c02v1InvertGpo4Pol OBJECT-TYPE
			SYNTAX Bit0No1Yes
			MAX-ACCESS read-write
			STATUS current
			DESCRIPTION
				"Allows inverting GPO4 polarity"
		::= { tle2001c02v1Entry 25 }

		-- 1.3.6.1.4.1.10106.3.101291.1.1.27
		tle2001c02v1Gpi1 OBJECT-TYPE
			SYNTAX Bit0Ina1Act
			MAX-ACCESS read-only
			STATUS current
			DESCRIPTION
				"GPI1 status"
		::= { tle2001c02v1Entry 27 }

		-- 1.3.6.1.4.1.10106.3.101291.1.1.28
		tle2001c02v1Gpi1TrapEnable OBJECT-TYPE
			SYNTAX AlarmEnable
			MAX-ACCESS read-write
			STATUS current
			DESCRIPTION
				"GPI1 status Trap Enable"
		::= { tle2001c02v1Entry 28 }

		-- 1.3.6.1.4.1.10106.3.101291.1.1.29
		tle2001c02v1Gpi2 OBJECT-TYPE
			SYNTAX Bit0Ina1Act
			MAX-ACCESS read-only
			STATUS current
			DESCRIPTION
				"GPI2 status"
		::= { tle2001c02v1Entry 29 }

		-- 1.3.6.1.4.1.10106.3.101291.1.1.30
		tle2001c02v1Gpi2TrapEnable OBJECT-TYPE
			SYNTAX AlarmEnable
			MAX-ACCESS read-write
			STATUS current
			DESCRIPTION
				"GPI2 status Trap Enable"
		::= { tle2001c02v1Entry 30 }

		-- 1.3.6.1.4.1.10106.3.101291.1.1.31
		tle2001c02v1Gpi3 OBJECT-TYPE
			SYNTAX Bit0Ina1Act
			MAX-ACCESS read-only
			STATUS current
			DESCRIPTION
				"GPI3 status"
		::= { tle2001c02v1Entry 31 }

		-- 1.3.6.1.4.1.10106.3.101291.1.1.32
		tle2001c02v1Gpi3TrapEnable OBJECT-TYPE
			SYNTAX AlarmEnable
			MAX-ACCESS read-write
			STATUS current
			DESCRIPTION
				"GPI3 status Trap Enable"
		::= { tle2001c02v1Entry 32 }

		-- 1.3.6.1.4.1.10106.3.101291.1.1.33
		tle2001c02v1Gpi4 OBJECT-TYPE
			SYNTAX Bit0Ina1Act
			MAX-ACCESS read-only
			STATUS current
			DESCRIPTION
				"GPI4 status"
		::= { tle2001c02v1Entry 33 }

		-- 1.3.6.1.4.1.10106.3.101291.1.1.34
		tle2001c02v1Gpi4TrapEnable OBJECT-TYPE
			SYNTAX AlarmEnable
			MAX-ACCESS read-write
			STATUS current
			DESCRIPTION
				"GPI4 status Trap Enable"
		::= { tle2001c02v1Entry 34 }

		-- 1.3.6.1.4.1.10106.3.101291.1.1.35
		tle2001c02v1RedBoard OBJECT-TYPE
			SYNTAX Bit0No1Yes
			MAX-ACCESS read-only
			STATUS current
			DESCRIPTION
				"Indicates that there are two modules in redundant configuration"
		::= { tle2001c02v1Entry 35 }

		-- 1.3.6.1.4.1.10106.3.101291.1.1.36
		tle2001c02v1RedBoardTrapEnable OBJECT-TYPE
			SYNTAX AlarmEnable
			MAX-ACCESS read-write
			STATUS current
			DESCRIPTION
				"Indicates that there are two modules in redundant configuration Trap Enable"
		::= { tle2001c02v1Entry 36 }

		-- 1.3.6.1.4.1.10106.3.101291.1.1.37
		tle2001c02v1EthLink OBJECT-TYPE
			SYNTAX Bit0No1Yes
			MAX-ACCESS read-only
			STATUS current
			DESCRIPTION
				"Indicates that the Ethernet link is OK"
		::= { tle2001c02v1Entry 37 }

		-- 1.3.6.1.4.1.10106.3.101291.1.1.38
		tle2001c02v1EthLinkTrapEnable OBJECT-TYPE
			SYNTAX AlarmEnable
			MAX-ACCESS read-write
			STATUS current
			DESCRIPTION
				"Indicates that the Ethernet link is OK Trap Enable"
		::= { tle2001c02v1Entry 38 }

		-- 1.3.6.1.4.1.10106.3.101291.1.1.39
		tle2001c02v1EthRedAct OBJECT-TYPE
			SYNTAX Bit0No1Yes
			MAX-ACCESS read-only
			STATUS current
			DESCRIPTION
				"Indicates that this is the active module of the redundant configuration"
		::= { tle2001c02v1Entry 39 }

		-- 1.3.6.1.4.1.10106.3.101291.1.1.40
		tle2001c02v1EthRedActTrapEnable OBJECT-TYPE
			SYNTAX AlarmEnable
			MAX-ACCESS read-write
			STATUS current
			DESCRIPTION
				"Indicates that this is the active module of the redundant configuration Trap Enable"
		::= { tle2001c02v1Entry 40 }

		-- 1.3.6.1.4.1.10106.3.101291.1.1.41
		tle2001c02v1SerialNo OBJECT-TYPE
			SYNTAX SerialNo
			MAX-ACCESS read-only
			STATUS current
			DESCRIPTION
				"Serial number"
		::= { tle2001c02v1Entry 41 }

		-- 1.3.6.1.4.1.10106.3.469001
		ddf2008c01v1 OBJECT IDENTIFIER ::= { albalaProducts 469001 }

		-- 1.3.6.1.4.1.10106.3.469001.1
		ddf2008c01v1Table  OBJECT-TYPE
			SYNTAX SEQUENCE OF Ddf2008c01v1Entry
			MAX-ACCESS not-accessible
			STATUS current
			DESCRIPTION
				"Module  DDF2008C01V1 Table"
			::= { ddf2008c01v1 1 }

		-- 1.3.6.1.4.1.10106.3.469001.1.1
		ddf2008c01v1Entry  OBJECT-TYPE
			SYNTAX Ddf2008c01v1Entry
			MAX-ACCESS not-accessible
			STATUS current
			DESCRIPTION
				"Module DDF2008C01V1 Entry"
			INDEX { ddf2008c01v1Index }
			::= { ddf2008c01v1Table 1 }

			Ddf2008c01v1Entry ::=
			SEQUENCE {
				ddf2008c01v1Index
				ModuleIndex,
				ddf2008c01v1ActivePreset
				Preset16Active,
				ddf2008c01v1LoadPreset
				Preset16Load,
				ddf2008c01v1SavePreset
				Preset16Save,
				ddf2008c01v1AesIoMode
				IoAesMode,
				ddf2008c01v1AudioFailMode
				AudioFailMode,
				ddf2008c01v1R2lOut1Src
				Hde2R2lSrc,
				ddf2008c01v1R2lOut2Src
				Hde2R2lSrc,
				ddf2008c01v1R2lOut3Src
				Hde2R2lSrc,
				ddf2008c01v1R2lOut4Src
				Hde2R2lSrc,
				ddf2008c01v1R2lOut5Src
				Hde2R2lSrc,
				ddf2008c01v1R2lOut6Src
				Hde2R2lSrc,
				ddf2008c01v1R2lOut7Src
				Hde2R2lSrc,
				ddf2008c01v1R2lOut8Src
				Hde2R2lSrc,
				ddf2008c01v1R2lOut9Src
				Hde2R2lSrc,
				ddf2008c01v1R2lOut10Src
				Hde2R2lSrc,
				ddf2008c01v1R2lOut11Src
				Hde2R2lSrc,
				ddf2008c01v1R2lOut12Src
				Hde2R2lSrc,
				ddf2008c01v1R2lOut13Src
				Hde2R2lSrc,
				ddf2008c01v1R2lOut14Src
				Hde2R2lSrc,
				ddf2008c01v1R2lOut15Src
				Hde2R2lSrc,
				ddf2008c01v1R2lOut16Src
				Hde2R2lSrc,
				ddf2008c01v1L2rOut1Src
				Hde2L2rSrc,
				ddf2008c01v1L2rOut2Src
				Hde2L2rSrc,
				ddf2008c01v1L2rOut3Src
				Hde2L2rSrc,
				ddf2008c01v1L2rOut4Src
				Hde2L2rSrc,
				ddf2008c01v1L2rOut5Src
				Hde2L2rSrc,
				ddf2008c01v1L2rOut6Src
				Hde2L2rSrc,
				ddf2008c01v1L2rOut7Src
				Hde2L2rSrc,
				ddf2008c01v1L2rOut8Src
				Hde2L2rSrc,
				ddf2008c01v1L2rOut9Src
				Hde2L2rSrc,
				ddf2008c01v1L2rOut10Src
				Hde2L2rSrc,
				ddf2008c01v1L2rOut11Src
				Hde2L2rSrc,
				ddf2008c01v1L2rOut12Src
				Hde2L2rSrc,
				ddf2008c01v1L2rOut13Src
				Hde2L2rSrc,
				ddf2008c01v1L2rOut14Src
				Hde2L2rSrc,
				ddf2008c01v1L2rOut15Src
				Hde2L2rSrc,
				ddf2008c01v1L2rOut16Src
				Hde2L2rSrc,
				ddf2008c01v1Aes1LOutSrc
				Hde2AesSrc,
				ddf2008c01v1Aes1ROutSrc
				Hde2AesSrc,
				ddf2008c01v1Aes2LOutSrc
				Hde2AesSrc,
				ddf2008c01v1Aes2ROutSrc
				Hde2AesSrc,
				ddf2008c01v1Aes3LOutSrc
				Hde2AesSrc,
				ddf2008c01v1Aes3ROutSrc
				Hde2AesSrc,
				ddf2008c01v1Aes4LOutSrc
				Hde2AesSrc,
				ddf2008c01v1Aes4ROutSrc
				Hde2AesSrc,
				ddf2008c01v1Aes5LOutSrc
				Hde2AesSrc,
				ddf2008c01v1Aes5ROutSrc
				Hde2AesSrc,
				ddf2008c01v1Aes6LOutSrc
				Hde2AesSrc,
				ddf2008c01v1Aes6ROutSrc
				Hde2AesSrc,
				ddf2008c01v1Aes7LOutSrc
				Hde2AesSrc,
				ddf2008c01v1Aes7ROutSrc
				Hde2AesSrc,
				ddf2008c01v1Aes8LOutSrc
				Hde2AesSrc,
				ddf2008c01v1Aes8ROutSrc
				Hde2AesSrc,
				ddf2008c01v1AesIn1Pres
				BitFailN,
				ddf2008c01v1AesIn2Pres
				BitFailN,
				ddf2008c01v1AesIn3Pres
				BitFailN,
				ddf2008c01v1AesIn4Pres
				BitFailN,
				ddf2008c01v1AesIn5Pres
				BitFailN,
				ddf2008c01v1AesIn6Pres
				BitFailN,
				ddf2008c01v1AesIn7Pres
				BitFailN,
				ddf2008c01v1AesIn8Pres
				BitFailN,
				ddf2008c01v1AesIn1Locked
				BitFailN,
				ddf2008c01v1AesIn2Locked
				BitFailN,
				ddf2008c01v1AesIn3Locked
				BitFailN,
				ddf2008c01v1AesIn4Locked
				BitFailN,
				ddf2008c01v1AesIn5Locked
				BitFailN,
				ddf2008c01v1AesIn6Locked
				BitFailN,
				ddf2008c01v1AesIn7Locked
				BitFailN,
				ddf2008c01v1AesIn8Locked
				BitFailN,
				ddf2008c01v1BackplaneLocked
				BitFailN,
				ddf2008c01v1BackplaneLockedTrapEnable
				AlarmEnable,
				ddf2008c01v1L2rIn1Pres
				BitFailN,
				ddf2008c01v1L2rIn2Pres
				BitFailN,
				ddf2008c01v1L2rIn3Pres
				BitFailN,
				ddf2008c01v1L2rIn4Pres
				BitFailN,
				ddf2008c01v1L2rIn5Pres
				BitFailN,
				ddf2008c01v1L2rIn6Pres
				BitFailN,
				ddf2008c01v1L2rIn7Pres
				BitFailN,
				ddf2008c01v1L2rIn8Pres
				BitFailN,
				ddf2008c01v1L2rIn9Pres
				BitFailN,
				ddf2008c01v1L2rIn10Pres
				BitFailN,
				ddf2008c01v1L2rIn11Pres
				BitFailN,
				ddf2008c01v1L2rIn12Pres
				BitFailN,
				ddf2008c01v1L2rIn13Pres
				BitFailN,
				ddf2008c01v1L2rIn14Pres
				BitFailN,
				ddf2008c01v1L2rIn15Pres
				BitFailN,
				ddf2008c01v1L2rIn16Pres
				BitFailN,
				ddf2008c01v1R2lIn1Pres
				BitFailN,
				ddf2008c01v1R2lIn2Pres
				BitFailN,
				ddf2008c01v1R2lIn3Pres
				BitFailN,
				ddf2008c01v1R2lIn4Pres
				BitFailN,
				ddf2008c01v1R2lIn5Pres
				BitFailN,
				ddf2008c01v1R2lIn6Pres
				BitFailN,
				ddf2008c01v1R2lIn7Pres
				BitFailN,
				ddf2008c01v1R2lIn8Pres
				BitFailN,
				ddf2008c01v1R2lIn9Pres
				BitFailN,
				ddf2008c01v1R2lIn10Pres
				BitFailN,
				ddf2008c01v1R2lIn11Pres
				BitFailN,
				ddf2008c01v1R2lIn12Pres
				BitFailN,
				ddf2008c01v1R2lIn13Pres
				BitFailN,
				ddf2008c01v1R2lIn14Pres
				BitFailN,
				ddf2008c01v1R2lIn15Pres
				BitFailN,
				ddf2008c01v1R2lIn16Pres
				BitFailN,
				ddf2008c01v1SerialNo
				SerialNo
			 }

		-- 1.3.6.1.4.1.10106.3.101291.1.1.1
		ddf2008c01v1Index OBJECT-TYPE
			SYNTAX ModuleIndex
			MAX-ACCESS read-only
			STATUS current
			DESCRIPTION
				"Index of DDF2008C01V1 Table"
		::= { ddf2008c01v1Entry 1 }

		-- 1.3.6.1.4.1.10106.3.101291.1.1.3
		ddf2008c01v1ActivePreset OBJECT-TYPE
			SYNTAX Preset16Active
			MAX-ACCESS read-only
			STATUS current
			DESCRIPTION
				"Shows the active preset"
		::= { ddf2008c01v1Entry 3 }

		-- 1.3.6.1.4.1.10106.3.101291.1.1.5
		ddf2008c01v1LoadPreset OBJECT-TYPE
			SYNTAX Preset16Load
			MAX-ACCESS read-write
			STATUS current
			DESCRIPTION
				"Allows loading a preset"
		::= { ddf2008c01v1Entry 5 }

		-- 1.3.6.1.4.1.10106.3.101291.1.1.7
		ddf2008c01v1SavePreset OBJECT-TYPE
			SYNTAX Preset16Save
			MAX-ACCESS read-write
			STATUS current
			DESCRIPTION
				"Allows saving a preset"
		::= { ddf2008c01v1Entry 7 }

		-- 1.3.6.1.4.1.10106.3.101291.1.1.9
		ddf2008c01v1AesIoMode OBJECT-TYPE
			SYNTAX IoAesMode
			MAX-ACCESS read-write
			STATUS current
			DESCRIPTION
				" I/O AES mode"
		::= { ddf2008c01v1Entry 9 }

		-- 1.3.6.1.4.1.10106.3.101291.1.1.11
		ddf2008c01v1AudioFailMode OBJECT-TYPE
			SYNTAX AudioFailMode
			MAX-ACCESS read-write
			STATUS current
			DESCRIPTION
				"Allows selecting the output signal when the source signal fails"
		::= { ddf2008c01v1Entry 11 }

		-- 1.3.6.1.4.1.10106.3.101291.1.1.13
		ddf2008c01v1R2lOut1Src OBJECT-TYPE
			SYNTAX Hde2R2lSrc
			MAX-ACCESS read-write
			STATUS current
			DESCRIPTION
				"Insertion source used in R2L OUT channel 1"
		::= { ddf2008c01v1Entry 13 }

		-- 1.3.6.1.4.1.10106.3.101291.1.1.15
		ddf2008c01v1R2lOut2Src OBJECT-TYPE
			SYNTAX Hde2R2lSrc
			MAX-ACCESS read-write
			STATUS current
			DESCRIPTION
				"Insertion source used in R2L OUT channel 2"
		::= { ddf2008c01v1Entry 15 }

		-- 1.3.6.1.4.1.10106.3.101291.1.1.17
		ddf2008c01v1R2lOut3Src OBJECT-TYPE
			SYNTAX Hde2R2lSrc
			MAX-ACCESS read-write
			STATUS current
			DESCRIPTION
				"Insertion source used in R2L OUT channel 3"
		::= { ddf2008c01v1Entry 17 }

		-- 1.3.6.1.4.1.10106.3.101291.1.1.19
		ddf2008c01v1R2lOut4Src OBJECT-TYPE
			SYNTAX Hde2R2lSrc
			MAX-ACCESS read-write
			STATUS current
			DESCRIPTION
				"Insertion source used in R2L OUT channel 4"
		::= { ddf2008c01v1Entry 19 }

		-- 1.3.6.1.4.1.10106.3.101291.1.1.21
		ddf2008c01v1R2lOut5Src OBJECT-TYPE
			SYNTAX Hde2R2lSrc
			MAX-ACCESS read-write
			STATUS current
			DESCRIPTION
				"Insertion source used in R2L OUT channel 5"
		::= { ddf2008c01v1Entry 21 }

		-- 1.3.6.1.4.1.10106.3.101291.1.1.23
		ddf2008c01v1R2lOut6Src OBJECT-TYPE
			SYNTAX Hde2R2lSrc
			MAX-ACCESS read-write
			STATUS current
			DESCRIPTION
				"Insertion source used in R2L OUT channel 6"
		::= { ddf2008c01v1Entry 23 }

		-- 1.3.6.1.4.1.10106.3.101291.1.1.25
		ddf2008c01v1R2lOut7Src OBJECT-TYPE
			SYNTAX Hde2R2lSrc
			MAX-ACCESS read-write
			STATUS current
			DESCRIPTION
				"Insertion source used in R2L OUT channel 7"
		::= { ddf2008c01v1Entry 25 }

		-- 1.3.6.1.4.1.10106.3.101291.1.1.27
		ddf2008c01v1R2lOut8Src OBJECT-TYPE
			SYNTAX Hde2R2lSrc
			MAX-ACCESS read-write
			STATUS current
			DESCRIPTION
				"Insertion source used in R2L OUT channel 8"
		::= { ddf2008c01v1Entry 27 }

		-- 1.3.6.1.4.1.10106.3.101291.1.1.29
		ddf2008c01v1R2lOut9Src OBJECT-TYPE
			SYNTAX Hde2R2lSrc
			MAX-ACCESS read-write
			STATUS current
			DESCRIPTION
				"Insertion source used in R2L OUT channel 9"
		::= { ddf2008c01v1Entry 29 }

		-- 1.3.6.1.4.1.10106.3.101291.1.1.31
		ddf2008c01v1R2lOut10Src OBJECT-TYPE
			SYNTAX Hde2R2lSrc
			MAX-ACCESS read-write
			STATUS current
			DESCRIPTION
				"Insertion source used in R2L OUT channel 10"
		::= { ddf2008c01v1Entry 31 }

		-- 1.3.6.1.4.1.10106.3.101291.1.1.33
		ddf2008c01v1R2lOut11Src OBJECT-TYPE
			SYNTAX Hde2R2lSrc
			MAX-ACCESS read-write
			STATUS current
			DESCRIPTION
				"Insertion source used in R2L OUT channel 11"
		::= { ddf2008c01v1Entry 33 }

		-- 1.3.6.1.4.1.10106.3.101291.1.1.35
		ddf2008c01v1R2lOut12Src OBJECT-TYPE
			SYNTAX Hde2R2lSrc
			MAX-ACCESS read-write
			STATUS current
			DESCRIPTION
				"Insertion source used in R2L OUT channel 12"
		::= { ddf2008c01v1Entry 35 }

		-- 1.3.6.1.4.1.10106.3.101291.1.1.37
		ddf2008c01v1R2lOut13Src OBJECT-TYPE
			SYNTAX Hde2R2lSrc
			MAX-ACCESS read-write
			STATUS current
			DESCRIPTION
				"Insertion source used in R2L OUT channel 13"
		::= { ddf2008c01v1Entry 37 }

		-- 1.3.6.1.4.1.10106.3.101291.1.1.39
		ddf2008c01v1R2lOut14Src OBJECT-TYPE
			SYNTAX Hde2R2lSrc
			MAX-ACCESS read-write
			STATUS current
			DESCRIPTION
				"Insertion source used in R2L OUT channel 14"
		::= { ddf2008c01v1Entry 39 }

		-- 1.3.6.1.4.1.10106.3.101291.1.1.41
		ddf2008c01v1R2lOut15Src OBJECT-TYPE
			SYNTAX Hde2R2lSrc
			MAX-ACCESS read-write
			STATUS current
			DESCRIPTION
				"Insertion source used in R2L OUT channel 15"
		::= { ddf2008c01v1Entry 41 }

		-- 1.3.6.1.4.1.10106.3.101291.1.1.43
		ddf2008c01v1R2lOut16Src OBJECT-TYPE
			SYNTAX Hde2R2lSrc
			MAX-ACCESS read-write
			STATUS current
			DESCRIPTION
				"Insertion source used in R2L OUT channel 16"
		::= { ddf2008c01v1Entry 43 }

		-- 1.3.6.1.4.1.10106.3.101291.1.1.45
		ddf2008c01v1L2rOut1Src OBJECT-TYPE
			SYNTAX Hde2L2rSrc
			MAX-ACCESS read-write
			STATUS current
			DESCRIPTION
				"Insertion source used in L2R OUT channel 1"
		::= { ddf2008c01v1Entry 45 }

		-- 1.3.6.1.4.1.10106.3.101291.1.1.47
		ddf2008c01v1L2rOut2Src OBJECT-TYPE
			SYNTAX Hde2L2rSrc
			MAX-ACCESS read-write
			STATUS current
			DESCRIPTION
				"Insertion source used in L2R OUT channel 2"
		::= { ddf2008c01v1Entry 47 }

		-- 1.3.6.1.4.1.10106.3.101291.1.1.49
		ddf2008c01v1L2rOut3Src OBJECT-TYPE
			SYNTAX Hde2L2rSrc
			MAX-ACCESS read-write
			STATUS current
			DESCRIPTION
				"Insertion source used in L2R OUT channel 3"
		::= { ddf2008c01v1Entry 49 }

		-- 1.3.6.1.4.1.10106.3.101291.1.1.51
		ddf2008c01v1L2rOut4Src OBJECT-TYPE
			SYNTAX Hde2L2rSrc
			MAX-ACCESS read-write
			STATUS current
			DESCRIPTION
				"Insertion source used in L2R OUT channel 4"
		::= { ddf2008c01v1Entry 51 }

		-- 1.3.6.1.4.1.10106.3.101291.1.1.53
		ddf2008c01v1L2rOut5Src OBJECT-TYPE
			SYNTAX Hde2L2rSrc
			MAX-ACCESS read-write
			STATUS current
			DESCRIPTION
				"Insertion source used in L2R OUT channel 5"
		::= { ddf2008c01v1Entry 53 }

		-- 1.3.6.1.4.1.10106.3.101291.1.1.55
		ddf2008c01v1L2rOut6Src OBJECT-TYPE
			SYNTAX Hde2L2rSrc
			MAX-ACCESS read-write
			STATUS current
			DESCRIPTION
				"Insertion source used in L2R OUT channel 6"
		::= { ddf2008c01v1Entry 55 }

		-- 1.3.6.1.4.1.10106.3.101291.1.1.57
		ddf2008c01v1L2rOut7Src OBJECT-TYPE
			SYNTAX Hde2L2rSrc
			MAX-ACCESS read-write
			STATUS current
			DESCRIPTION
				"Insertion source used in L2R OUT channel 7"
		::= { ddf2008c01v1Entry 57 }

		-- 1.3.6.1.4.1.10106.3.101291.1.1.59
		ddf2008c01v1L2rOut8Src OBJECT-TYPE
			SYNTAX Hde2L2rSrc
			MAX-ACCESS read-write
			STATUS current
			DESCRIPTION
				"Insertion source used in L2R OUT channel 8"
		::= { ddf2008c01v1Entry 59 }

		-- 1.3.6.1.4.1.10106.3.101291.1.1.61
		ddf2008c01v1L2rOut9Src OBJECT-TYPE
			SYNTAX Hde2L2rSrc
			MAX-ACCESS read-write
			STATUS current
			DESCRIPTION
				"Insertion source used in L2R OUT channel 9"
		::= { ddf2008c01v1Entry 61 }

		-- 1.3.6.1.4.1.10106.3.101291.1.1.63
		ddf2008c01v1L2rOut10Src OBJECT-TYPE
			SYNTAX Hde2L2rSrc
			MAX-ACCESS read-write
			STATUS current
			DESCRIPTION
				"Insertion source used in L2R OUT channel 10"
		::= { ddf2008c01v1Entry 63 }

		-- 1.3.6.1.4.1.10106.3.101291.1.1.65
		ddf2008c01v1L2rOut11Src OBJECT-TYPE
			SYNTAX Hde2L2rSrc
			MAX-ACCESS read-write
			STATUS current
			DESCRIPTION
				"Insertion source used in L2R OUT channel 11"
		::= { ddf2008c01v1Entry 65 }

		-- 1.3.6.1.4.1.10106.3.101291.1.1.67
		ddf2008c01v1L2rOut12Src OBJECT-TYPE
			SYNTAX Hde2L2rSrc
			MAX-ACCESS read-write
			STATUS current
			DESCRIPTION
				"Insertion source used in L2R OUT channel 12"
		::= { ddf2008c01v1Entry 67 }

		-- 1.3.6.1.4.1.10106.3.101291.1.1.69
		ddf2008c01v1L2rOut13Src OBJECT-TYPE
			SYNTAX Hde2L2rSrc
			MAX-ACCESS read-write
			STATUS current
			DESCRIPTION
				"Insertion source used in L2R OUT channel 13"
		::= { ddf2008c01v1Entry 69 }

		-- 1.3.6.1.4.1.10106.3.101291.1.1.71
		ddf2008c01v1L2rOut14Src OBJECT-TYPE
			SYNTAX Hde2L2rSrc
			MAX-ACCESS read-write
			STATUS current
			DESCRIPTION
				"Insertion source used in L2R OUT channel 14"
		::= { ddf2008c01v1Entry 71 }

		-- 1.3.6.1.4.1.10106.3.101291.1.1.73
		ddf2008c01v1L2rOut15Src OBJECT-TYPE
			SYNTAX Hde2L2rSrc
			MAX-ACCESS read-write
			STATUS current
			DESCRIPTION
				"Insertion source used in L2R OUT channel 15"
		::= { ddf2008c01v1Entry 73 }

		-- 1.3.6.1.4.1.10106.3.101291.1.1.75
		ddf2008c01v1L2rOut16Src OBJECT-TYPE
			SYNTAX Hde2L2rSrc
			MAX-ACCESS read-write
			STATUS current
			DESCRIPTION
				"Insertion source used in L2R OUT channel 16"
		::= { ddf2008c01v1Entry 75 }

		-- 1.3.6.1.4.1.10106.3.101291.1.1.77
		ddf2008c01v1Aes1LOutSrc OBJECT-TYPE
			SYNTAX Hde2AesSrc
			MAX-ACCESS read-write
			STATUS current
			DESCRIPTION
				"Insertion source used in AES1 channel left when used as output"
		::= { ddf2008c01v1Entry 77 }

		-- 1.3.6.1.4.1.10106.3.101291.1.1.79
		ddf2008c01v1Aes1ROutSrc OBJECT-TYPE
			SYNTAX Hde2AesSrc
			MAX-ACCESS read-write
			STATUS current
			DESCRIPTION
				"Insertion source used in AES1 channel right when used as output"
		::= { ddf2008c01v1Entry 79 }

		-- 1.3.6.1.4.1.10106.3.101291.1.1.81
		ddf2008c01v1Aes2LOutSrc OBJECT-TYPE
			SYNTAX Hde2AesSrc
			MAX-ACCESS read-write
			STATUS current
			DESCRIPTION
				"Insertion source used in AES2 channel left when used as output"
		::= { ddf2008c01v1Entry 81 }

		-- 1.3.6.1.4.1.10106.3.101291.1.1.83
		ddf2008c01v1Aes2ROutSrc OBJECT-TYPE
			SYNTAX Hde2AesSrc
			MAX-ACCESS read-write
			STATUS current
			DESCRIPTION
				"Insertion source used in AES2 channel right when used as output"
		::= { ddf2008c01v1Entry 83 }

		-- 1.3.6.1.4.1.10106.3.101291.1.1.85
		ddf2008c01v1Aes3LOutSrc OBJECT-TYPE
			SYNTAX Hde2AesSrc
			MAX-ACCESS read-write
			STATUS current
			DESCRIPTION
				"Insertion source used in AES3 channel left when used as output"
		::= { ddf2008c01v1Entry 85 }

		-- 1.3.6.1.4.1.10106.3.101291.1.1.87
		ddf2008c01v1Aes3ROutSrc OBJECT-TYPE
			SYNTAX Hde2AesSrc
			MAX-ACCESS read-write
			STATUS current
			DESCRIPTION
				"Insertion source used in AES3 channel right when used as output"
		::= { ddf2008c01v1Entry 87 }

		-- 1.3.6.1.4.1.10106.3.101291.1.1.89
		ddf2008c01v1Aes4LOutSrc OBJECT-TYPE
			SYNTAX Hde2AesSrc
			MAX-ACCESS read-write
			STATUS current
			DESCRIPTION
				"Insertion source used in AES4 channel left when used as output"
		::= { ddf2008c01v1Entry 89 }

		-- 1.3.6.1.4.1.10106.3.101291.1.1.91
		ddf2008c01v1Aes4ROutSrc OBJECT-TYPE
			SYNTAX Hde2AesSrc
			MAX-ACCESS read-write
			STATUS current
			DESCRIPTION
				"Insertion source used in AES4 channel right when used as output"
		::= { ddf2008c01v1Entry 91 }

		-- 1.3.6.1.4.1.10106.3.101291.1.1.93
		ddf2008c01v1Aes5LOutSrc OBJECT-TYPE
			SYNTAX Hde2AesSrc
			MAX-ACCESS read-write
			STATUS current
			DESCRIPTION
				"Insertion source used in AES5 channel left when used as output"
		::= { ddf2008c01v1Entry 93 }

		-- 1.3.6.1.4.1.10106.3.101291.1.1.95
		ddf2008c01v1Aes5ROutSrc OBJECT-TYPE
			SYNTAX Hde2AesSrc
			MAX-ACCESS read-write
			STATUS current
			DESCRIPTION
				"Insertion source used in AES5 channel right when used as output"
		::= { ddf2008c01v1Entry 95 }

		-- 1.3.6.1.4.1.10106.3.101291.1.1.97
		ddf2008c01v1Aes6LOutSrc OBJECT-TYPE
			SYNTAX Hde2AesSrc
			MAX-ACCESS read-write
			STATUS current
			DESCRIPTION
				"Insertion source used in AES6 channel left when used as output"
		::= { ddf2008c01v1Entry 97 }

		-- 1.3.6.1.4.1.10106.3.101291.1.1.99
		ddf2008c01v1Aes6ROutSrc OBJECT-TYPE
			SYNTAX Hde2AesSrc
			MAX-ACCESS read-write
			STATUS current
			DESCRIPTION
				"Insertion source used in AES6 channel right when used as output"
		::= { ddf2008c01v1Entry 99 }

		-- 1.3.6.1.4.1.10106.3.101291.1.1.101
		ddf2008c01v1Aes7LOutSrc OBJECT-TYPE
			SYNTAX Hde2AesSrc
			MAX-ACCESS read-write
			STATUS current
			DESCRIPTION
				"Insertion source used in AES7 channel left when used as output"
		::= { ddf2008c01v1Entry 101 }

		-- 1.3.6.1.4.1.10106.3.101291.1.1.103
		ddf2008c01v1Aes7ROutSrc OBJECT-TYPE
			SYNTAX Hde2AesSrc
			MAX-ACCESS read-write
			STATUS current
			DESCRIPTION
				"Insertion source used in AES7 channel right when used as output"
		::= { ddf2008c01v1Entry 103 }

		-- 1.3.6.1.4.1.10106.3.101291.1.1.105
		ddf2008c01v1Aes8LOutSrc OBJECT-TYPE
			SYNTAX Hde2AesSrc
			MAX-ACCESS read-write
			STATUS current
			DESCRIPTION
				"Insertion source used in AES8 channel left when used as output"
		::= { ddf2008c01v1Entry 105 }

		-- 1.3.6.1.4.1.10106.3.101291.1.1.107
		ddf2008c01v1Aes8ROutSrc OBJECT-TYPE
			SYNTAX Hde2AesSrc
			MAX-ACCESS read-write
			STATUS current
			DESCRIPTION
				"Insertion source used in AES8 channel right when used as output"
		::= { ddf2008c01v1Entry 107 }

		-- 1.3.6.1.4.1.10106.3.101291.1.1.109
		ddf2008c01v1AesIn1Pres OBJECT-TYPE
			SYNTAX BitFailN
			MAX-ACCESS read-only
			STATUS current
			DESCRIPTION
				"AES1 IN presence (valid signal)"
		::= { ddf2008c01v1Entry 109 }

		-- 1.3.6.1.4.1.10106.3.101291.1.1.111
		ddf2008c01v1AesIn2Pres OBJECT-TYPE
			SYNTAX BitFailN
			MAX-ACCESS read-only
			STATUS current
			DESCRIPTION
				"AES2 IN presence (valid signal)"
		::= { ddf2008c01v1Entry 111 }

		-- 1.3.6.1.4.1.10106.3.101291.1.1.113
		ddf2008c01v1AesIn3Pres OBJECT-TYPE
			SYNTAX BitFailN
			MAX-ACCESS read-only
			STATUS current
			DESCRIPTION
				"AES3 IN presence (valid signal)"
		::= { ddf2008c01v1Entry 113 }

		-- 1.3.6.1.4.1.10106.3.101291.1.1.115
		ddf2008c01v1AesIn4Pres OBJECT-TYPE
			SYNTAX BitFailN
			MAX-ACCESS read-only
			STATUS current
			DESCRIPTION
				"AES4 IN presence (valid signal)"
		::= { ddf2008c01v1Entry 115 }

		-- 1.3.6.1.4.1.10106.3.101291.1.1.117
		ddf2008c01v1AesIn5Pres OBJECT-TYPE
			SYNTAX BitFailN
			MAX-ACCESS read-only
			STATUS current
			DESCRIPTION
				"AES5 IN presence (valid signal)"
		::= { ddf2008c01v1Entry 117 }

		-- 1.3.6.1.4.1.10106.3.101291.1.1.119
		ddf2008c01v1AesIn6Pres OBJECT-TYPE
			SYNTAX BitFailN
			MAX-ACCESS read-only
			STATUS current
			DESCRIPTION
				"AES6 IN presence (valid signal)"
		::= { ddf2008c01v1Entry 119 }

		-- 1.3.6.1.4.1.10106.3.101291.1.1.121
		ddf2008c01v1AesIn7Pres OBJECT-TYPE
			SYNTAX BitFailN
			MAX-ACCESS read-only
			STATUS current
			DESCRIPTION
				"AES7 IN presence (valid signal)"
		::= { ddf2008c01v1Entry 121 }

		-- 1.3.6.1.4.1.10106.3.101291.1.1.123
		ddf2008c01v1AesIn8Pres OBJECT-TYPE
			SYNTAX BitFailN
			MAX-ACCESS read-only
			STATUS current
			DESCRIPTION
				"AES8 IN presence (valid signal)"
		::= { ddf2008c01v1Entry 123 }

		-- 1.3.6.1.4.1.10106.3.101291.1.1.125
		ddf2008c01v1AesIn1Locked OBJECT-TYPE
			SYNTAX BitFailN
			MAX-ACCESS read-only
			STATUS current
			DESCRIPTION
				"AES1 IN locked (synchronized with internal clock)"
		::= { ddf2008c01v1Entry 125 }

		-- 1.3.6.1.4.1.10106.3.101291.1.1.127
		ddf2008c01v1AesIn2Locked OBJECT-TYPE
			SYNTAX BitFailN
			MAX-ACCESS read-only
			STATUS current
			DESCRIPTION
				"AES2 IN locked (synchronized with internal clock)"
		::= { ddf2008c01v1Entry 127 }

		-- 1.3.6.1.4.1.10106.3.101291.1.1.129
		ddf2008c01v1AesIn3Locked OBJECT-TYPE
			SYNTAX BitFailN
			MAX-ACCESS read-only
			STATUS current
			DESCRIPTION
				"AES3 IN locked (synchronized with internal clock)"
		::= { ddf2008c01v1Entry 129 }

		-- 1.3.6.1.4.1.10106.3.101291.1.1.131
		ddf2008c01v1AesIn4Locked OBJECT-TYPE
			SYNTAX BitFailN
			MAX-ACCESS read-only
			STATUS current
			DESCRIPTION
				"AES4 IN locked (synchronized with internal clock)"
		::= { ddf2008c01v1Entry 131 }

		-- 1.3.6.1.4.1.10106.3.101291.1.1.133
		ddf2008c01v1AesIn5Locked OBJECT-TYPE
			SYNTAX BitFailN
			MAX-ACCESS read-only
			STATUS current
			DESCRIPTION
				"AES5 IN locked (synchronized with internal clock)"
		::= { ddf2008c01v1Entry 133 }

		-- 1.3.6.1.4.1.10106.3.101291.1.1.135
		ddf2008c01v1AesIn6Locked OBJECT-TYPE
			SYNTAX BitFailN
			MAX-ACCESS read-only
			STATUS current
			DESCRIPTION
				"AES6 IN locked (synchronized with internal clock)"
		::= { ddf2008c01v1Entry 135 }

		-- 1.3.6.1.4.1.10106.3.101291.1.1.137
		ddf2008c01v1AesIn7Locked OBJECT-TYPE
			SYNTAX BitFailN
			MAX-ACCESS read-only
			STATUS current
			DESCRIPTION
				"AES7 IN locked (synchronized with internal clock)"
		::= { ddf2008c01v1Entry 137 }

		-- 1.3.6.1.4.1.10106.3.101291.1.1.139
		ddf2008c01v1AesIn8Locked OBJECT-TYPE
			SYNTAX BitFailN
			MAX-ACCESS read-only
			STATUS current
			DESCRIPTION
				"AES8 IN locked (synchronized with internal clock)"
		::= { ddf2008c01v1Entry 139 }

		-- 1.3.6.1.4.1.10106.3.101291.1.1.141
		ddf2008c01v1BackplaneLocked OBJECT-TYPE
			SYNTAX BitFailN
			MAX-ACCESS read-only
			STATUS current
			DESCRIPTION
				"Locked to internal bus audio (MCLK and WCLK valid and locked)"
		::= { ddf2008c01v1Entry 141 }

		-- 1.3.6.1.4.1.10106.3.101291.1.1.142
		ddf2008c01v1BackplaneLockedTrapEnable OBJECT-TYPE
			SYNTAX AlarmEnable
			MAX-ACCESS read-write
			STATUS current
			DESCRIPTION
				"Locked to internal bus audio (MCLK and WCLK valid and locked) Trap Enable"
		::= { ddf2008c01v1Entry 142 }

		-- 1.3.6.1.4.1.10106.3.101291.1.1.143
		ddf2008c01v1L2rIn1Pres OBJECT-TYPE
			SYNTAX BitFailN
			MAX-ACCESS read-only
			STATUS current
			DESCRIPTION
				"There is a valid audio signal in channel 1 of  L2R IN"
		::= { ddf2008c01v1Entry 143 }

		-- 1.3.6.1.4.1.10106.3.101291.1.1.145
		ddf2008c01v1L2rIn2Pres OBJECT-TYPE
			SYNTAX BitFailN
			MAX-ACCESS read-only
			STATUS current
			DESCRIPTION
				"There is a valid audio signal in channel 2 of  L2R IN"
		::= { ddf2008c01v1Entry 145 }

		-- 1.3.6.1.4.1.10106.3.101291.1.1.147
		ddf2008c01v1L2rIn3Pres OBJECT-TYPE
			SYNTAX BitFailN
			MAX-ACCESS read-only
			STATUS current
			DESCRIPTION
				"There is a valid audio signal in channel 3 of  L2R IN"
		::= { ddf2008c01v1Entry 147 }

		-- 1.3.6.1.4.1.10106.3.101291.1.1.149
		ddf2008c01v1L2rIn4Pres OBJECT-TYPE
			SYNTAX BitFailN
			MAX-ACCESS read-only
			STATUS current
			DESCRIPTION
				"There is a valid audio signal in channel 4 of  L2R IN"
		::= { ddf2008c01v1Entry 149 }

		-- 1.3.6.1.4.1.10106.3.101291.1.1.151
		ddf2008c01v1L2rIn5Pres OBJECT-TYPE
			SYNTAX BitFailN
			MAX-ACCESS read-only
			STATUS current
			DESCRIPTION
				"There is a valid audio signal in channel 5 of  L2R IN"
		::= { ddf2008c01v1Entry 151 }

		-- 1.3.6.1.4.1.10106.3.101291.1.1.153
		ddf2008c01v1L2rIn6Pres OBJECT-TYPE
			SYNTAX BitFailN
			MAX-ACCESS read-only
			STATUS current
			DESCRIPTION
				"There is a valid audio signal in channel 6 of  L2R IN"
		::= { ddf2008c01v1Entry 153 }

		-- 1.3.6.1.4.1.10106.3.101291.1.1.155
		ddf2008c01v1L2rIn7Pres OBJECT-TYPE
			SYNTAX BitFailN
			MAX-ACCESS read-only
			STATUS current
			DESCRIPTION
				"There is a valid audio signal in channel 7 of  L2R IN"
		::= { ddf2008c01v1Entry 155 }

		-- 1.3.6.1.4.1.10106.3.101291.1.1.157
		ddf2008c01v1L2rIn8Pres OBJECT-TYPE
			SYNTAX BitFailN
			MAX-ACCESS read-only
			STATUS current
			DESCRIPTION
				"There is a valid audio signal in channel 8 of  L2R IN"
		::= { ddf2008c01v1Entry 157 }

		-- 1.3.6.1.4.1.10106.3.101291.1.1.159
		ddf2008c01v1L2rIn9Pres OBJECT-TYPE
			SYNTAX BitFailN
			MAX-ACCESS read-only
			STATUS current
			DESCRIPTION
				"There is a valid audio signal in channel 9 of  L2R IN"
		::= { ddf2008c01v1Entry 159 }

		-- 1.3.6.1.4.1.10106.3.101291.1.1.161
		ddf2008c01v1L2rIn10Pres OBJECT-TYPE
			SYNTAX BitFailN
			MAX-ACCESS read-only
			STATUS current
			DESCRIPTION
				"There is a valid audio signal in channel 10 of  L2R IN"
		::= { ddf2008c01v1Entry 161 }

		-- 1.3.6.1.4.1.10106.3.101291.1.1.163
		ddf2008c01v1L2rIn11Pres OBJECT-TYPE
			SYNTAX BitFailN
			MAX-ACCESS read-only
			STATUS current
			DESCRIPTION
				"There is a valid audio signal in channel 11 of  L2R IN"
		::= { ddf2008c01v1Entry 163 }

		-- 1.3.6.1.4.1.10106.3.101291.1.1.165
		ddf2008c01v1L2rIn12Pres OBJECT-TYPE
			SYNTAX BitFailN
			MAX-ACCESS read-only
			STATUS current
			DESCRIPTION
				"There is a valid audio signal in channel 12 of  L2R IN"
		::= { ddf2008c01v1Entry 165 }

		-- 1.3.6.1.4.1.10106.3.101291.1.1.167
		ddf2008c01v1L2rIn13Pres OBJECT-TYPE
			SYNTAX BitFailN
			MAX-ACCESS read-only
			STATUS current
			DESCRIPTION
				"There is a valid audio signal in channel 13 of  L2R IN"
		::= { ddf2008c01v1Entry 167 }

		-- 1.3.6.1.4.1.10106.3.101291.1.1.169
		ddf2008c01v1L2rIn14Pres OBJECT-TYPE
			SYNTAX BitFailN
			MAX-ACCESS read-only
			STATUS current
			DESCRIPTION
				"There is a valid audio signal in channel 14 of  L2R IN"
		::= { ddf2008c01v1Entry 169 }

		-- 1.3.6.1.4.1.10106.3.101291.1.1.171
		ddf2008c01v1L2rIn15Pres OBJECT-TYPE
			SYNTAX BitFailN
			MAX-ACCESS read-only
			STATUS current
			DESCRIPTION
				"There is a valid audio signal in channel 15 of  L2R IN"
		::= { ddf2008c01v1Entry 171 }

		-- 1.3.6.1.4.1.10106.3.101291.1.1.173
		ddf2008c01v1L2rIn16Pres OBJECT-TYPE
			SYNTAX BitFailN
			MAX-ACCESS read-only
			STATUS current
			DESCRIPTION
				"There is a valid audio signal in channel 16 of  L2R IN"
		::= { ddf2008c01v1Entry 173 }

		-- 1.3.6.1.4.1.10106.3.101291.1.1.175
		ddf2008c01v1R2lIn1Pres OBJECT-TYPE
			SYNTAX BitFailN
			MAX-ACCESS read-only
			STATUS current
			DESCRIPTION
				"There is a valid audio signal in channel 1 of  R2L IN"
		::= { ddf2008c01v1Entry 175 }

		-- 1.3.6.1.4.1.10106.3.101291.1.1.177
		ddf2008c01v1R2lIn2Pres OBJECT-TYPE
			SYNTAX BitFailN
			MAX-ACCESS read-only
			STATUS current
			DESCRIPTION
				"There is a valid audio signal in channel 2 of  R2L IN"
		::= { ddf2008c01v1Entry 177 }

		-- 1.3.6.1.4.1.10106.3.101291.1.1.179
		ddf2008c01v1R2lIn3Pres OBJECT-TYPE
			SYNTAX BitFailN
			MAX-ACCESS read-only
			STATUS current
			DESCRIPTION
				"There is a valid audio signal in channel 3 of  R2L IN"
		::= { ddf2008c01v1Entry 179 }

		-- 1.3.6.1.4.1.10106.3.101291.1.1.181
		ddf2008c01v1R2lIn4Pres OBJECT-TYPE
			SYNTAX BitFailN
			MAX-ACCESS read-only
			STATUS current
			DESCRIPTION
				"There is a valid audio signal in channel 4 of  R2L IN"
		::= { ddf2008c01v1Entry 181 }

		-- 1.3.6.1.4.1.10106.3.101291.1.1.183
		ddf2008c01v1R2lIn5Pres OBJECT-TYPE
			SYNTAX BitFailN
			MAX-ACCESS read-only
			STATUS current
			DESCRIPTION
				"There is a valid audio signal in channel 5 of  R2L IN"
		::= { ddf2008c01v1Entry 183 }

		-- 1.3.6.1.4.1.10106.3.101291.1.1.185
		ddf2008c01v1R2lIn6Pres OBJECT-TYPE
			SYNTAX BitFailN
			MAX-ACCESS read-only
			STATUS current
			DESCRIPTION
				"There is a valid audio signal in channel 6 of  R2L IN"
		::= { ddf2008c01v1Entry 185 }

		-- 1.3.6.1.4.1.10106.3.101291.1.1.187
		ddf2008c01v1R2lIn7Pres OBJECT-TYPE
			SYNTAX BitFailN
			MAX-ACCESS read-only
			STATUS current
			DESCRIPTION
				"There is a valid audio signal in channel 7 of  R2L IN"
		::= { ddf2008c01v1Entry 187 }

		-- 1.3.6.1.4.1.10106.3.101291.1.1.189
		ddf2008c01v1R2lIn8Pres OBJECT-TYPE
			SYNTAX BitFailN
			MAX-ACCESS read-only
			STATUS current
			DESCRIPTION
				"There is a valid audio signal in channel 8 of  R2L IN"
		::= { ddf2008c01v1Entry 189 }

		-- 1.3.6.1.4.1.10106.3.101291.1.1.191
		ddf2008c01v1R2lIn9Pres OBJECT-TYPE
			SYNTAX BitFailN
			MAX-ACCESS read-only
			STATUS current
			DESCRIPTION
				"There is a valid audio signal in channel 9 of  R2L IN"
		::= { ddf2008c01v1Entry 191 }

		-- 1.3.6.1.4.1.10106.3.101291.1.1.193
		ddf2008c01v1R2lIn10Pres OBJECT-TYPE
			SYNTAX BitFailN
			MAX-ACCESS read-only
			STATUS current
			DESCRIPTION
				"There is a valid audio signal in channel 10 of  R2L IN"
		::= { ddf2008c01v1Entry 193 }

		-- 1.3.6.1.4.1.10106.3.101291.1.1.195
		ddf2008c01v1R2lIn11Pres OBJECT-TYPE
			SYNTAX BitFailN
			MAX-ACCESS read-only
			STATUS current
			DESCRIPTION
				"There is a valid audio signal in channel 11 of  R2L IN"
		::= { ddf2008c01v1Entry 195 }

		-- 1.3.6.1.4.1.10106.3.101291.1.1.197
		ddf2008c01v1R2lIn12Pres OBJECT-TYPE
			SYNTAX BitFailN
			MAX-ACCESS read-only
			STATUS current
			DESCRIPTION
				"There is a valid audio signal in channel 12 of  R2L IN"
		::= { ddf2008c01v1Entry 197 }

		-- 1.3.6.1.4.1.10106.3.101291.1.1.199
		ddf2008c01v1R2lIn13Pres OBJECT-TYPE
			SYNTAX BitFailN
			MAX-ACCESS read-only
			STATUS current
			DESCRIPTION
				"There is a valid audio signal in channel 13 of  R2L IN"
		::= { ddf2008c01v1Entry 199 }

		-- 1.3.6.1.4.1.10106.3.101291.1.1.201
		ddf2008c01v1R2lIn14Pres OBJECT-TYPE
			SYNTAX BitFailN
			MAX-ACCESS read-only
			STATUS current
			DESCRIPTION
				"There is a valid audio signal in channel 14 of  R2L IN"
		::= { ddf2008c01v1Entry 201 }

		-- 1.3.6.1.4.1.10106.3.101291.1.1.203
		ddf2008c01v1R2lIn15Pres OBJECT-TYPE
			SYNTAX BitFailN
			MAX-ACCESS read-only
			STATUS current
			DESCRIPTION
				"There is a valid audio signal in channel 15 of  R2L IN"
		::= { ddf2008c01v1Entry 203 }

		-- 1.3.6.1.4.1.10106.3.101291.1.1.205
		ddf2008c01v1R2lIn16Pres OBJECT-TYPE
			SYNTAX BitFailN
			MAX-ACCESS read-only
			STATUS current
			DESCRIPTION
				"There is a valid audio signal in channel 16 of  R2L IN"
		::= { ddf2008c01v1Entry 205 }

		-- 1.3.6.1.4.1.10106.3.101291.1.1.207
		ddf2008c01v1SerialNo OBJECT-TYPE
			SYNTAX SerialNo
			MAX-ACCESS read-only
			STATUS current
			DESCRIPTION
				"Serial number"
		::= { ddf2008c01v1Entry 207 }

		-- 1.3.6.1.4.1.10106.3.470001
		hfs2000c01v1 OBJECT IDENTIFIER ::= { albalaProducts 470001 }

		-- 1.3.6.1.4.1.10106.3.470001.1
		hfs2000c01v1Table  OBJECT-TYPE
			SYNTAX SEQUENCE OF Hfs2000c01v1Entry
			MAX-ACCESS not-accessible
			STATUS current
			DESCRIPTION
				"Module  HFS2000C01V1 Table"
			::= { hfs2000c01v1 1 }

		-- 1.3.6.1.4.1.10106.3.470001.1.1
		hfs2000c01v1Entry  OBJECT-TYPE
			SYNTAX Hfs2000c01v1Entry
			MAX-ACCESS not-accessible
			STATUS current
			DESCRIPTION
				"Module HFS2000C01V1 Entry"
			INDEX { hfs2000c01v1Index }
			::= { hfs2000c01v1Table 1 }

			Hfs2000c01v1Entry ::=
			SEQUENCE {
				hfs2000c01v1Index
				ModuleIndex,
				hfs2000c01v1SynchroMode
				Bit0Fra1Lin,
				hfs2000c01v1FailMode
				Bit0Fre1Blk,
				hfs2000c01v1VbiMode
				Bit0Pas1Bnk,
				hfs2000c01v1DelayMode
				Bit0Syn1De2,
				hfs2000c01v1HDelay
				DelayPixel5,
				hfs2000c01v1FrameDelay
				DelayFram4,
				hfs2000c01v1VDelay
				DelayLines2,
				hfs2000c01v1LumaGain
				GainLin1,
				hfs2000c01v1ChromaGain
				GainLin1,
				hfs2000c01v1BlackOffset
				BlackOffset1,
				hfs2000c01v1Bits
				Bit020124,
				hfs2000c01v1Grp1P0lSrc
				AudioSource,
				hfs2000c01v1Grp1P0rSrc
				AudioSource,
				hfs2000c01v1Grp1P1lSrc
				AudioSource,
				hfs2000c01v1Grp1P1rSrc
				AudioSource,
				hfs2000c01v1Grp1P0l
				AudioMxInput7,
				hfs2000c01v1Grp1P0r
				AudioMxInput7,
				hfs2000c01v1Grp1P1l
				AudioMxInput7,
				hfs2000c01v1Grp1P1r
				AudioMxInput7,
				hfs2000c01v1Grp2P0lSrc
				AudioSource,
				hfs2000c01v1Grp2P0rSrc
				AudioSource,
				hfs2000c01v1Grp2P1lSrc
				AudioSource,
				hfs2000c01v1Grp2P1rSrc
				AudioSource,
				hfs2000c01v1Grp2P0l
				AudioMxInput7,
				hfs2000c01v1Grp2P0r
				AudioMxInput7,
				hfs2000c01v1Grp2P1l
				AudioMxInput7,
				hfs2000c01v1Grp2P1r
				AudioMxInput7,
				hfs2000c01v1Grp3P0lSrc
				AudioSource,
				hfs2000c01v1Grp3P0rSrc
				AudioSource,
				hfs2000c01v1Grp3P1lSrc
				AudioSource,
				hfs2000c01v1Grp3P1rSrc
				AudioSource,
				hfs2000c01v1Grp3P0l
				AudioMxInput7,
				hfs2000c01v1Grp3P0r
				AudioMxInput7,
				hfs2000c01v1Grp3P1l
				AudioMxInput7,
				hfs2000c01v1Grp3P1r
				AudioMxInput7,
				hfs2000c01v1Grp4P0lSrc
				AudioSource,
				hfs2000c01v1Grp4P0rSrc
				AudioSource,
				hfs2000c01v1Grp4P1lSrc
				AudioSource,
				hfs2000c01v1Grp4P1rSrc
				AudioSource,
				hfs2000c01v1Grp4P0l
				AudioMxInput7,
				hfs2000c01v1Grp4P0r
				AudioMxInput7,
				hfs2000c01v1Grp4P1l
				AudioMxInput7,
				hfs2000c01v1Grp4P1r
				AudioMxInput7,
				hfs2000c01v1NoSig
				BitFail,
				hfs2000c01v1NoSigTrapEnable
				AlarmEnable,
				hfs2000c01v1Unlock
				BitFail,
				hfs2000c01v1UnlockTrapEnable
				AlarmEnable,
				hfs2000c01v1EdhCrc
				BitFail,
				hfs2000c01v1EdhCrcTrapEnable
				AlarmEnable,
				hfs2000c01v1NoRef
				BitFail,
				hfs2000c01v1NoRefTrapEnable
				AlarmEnable,
				hfs2000c01v1RefUnlock
				BitFail,
				hfs2000c01v1RefUnlockTrapEnable
				AlarmEnable,
				hfs2000c01v1InputFormat
				SdiHd3gFmt3,
				hfs2000c01v1SdiFormat
				SdiHd3gFmt3,
				hfs2000c01v1SigDelay
				DelayX20Us,
				hfs2000c01v1Grp1Pres
				Bit0No1Yes,
				hfs2000c01v1Grp2Pres
				Bit0No1Yes,
				hfs2000c01v1Grp3Pres
				Bit0No1Yes,
				hfs2000c01v1Grp4Pres
				Bit0No1Yes,
				hfs2000c01v1Grp1P0Err
				BitFail,
				hfs2000c01v1Grp1P1Err
				BitFail,
				hfs2000c01v1Grp2P0Err
				BitFail,
				hfs2000c01v1Grp2P1Err
				BitFail,
				hfs2000c01v1Grp3P0Err
				BitFail,
				hfs2000c01v1Grp3P1Err
				BitFail,
				hfs2000c01v1Grp4P0Err
				BitFail,
				hfs2000c01v1Grp4P1Err
				BitFail,
				hfs2000c01v1R2lIn1Pres
				BitFail,
				hfs2000c01v1R2lIn2Pres
				BitFail,
				hfs2000c01v1R2lIn3Pres
				BitFail,
				hfs2000c01v1R2lIn4Pres
				BitFail,
				hfs2000c01v1R2lIn5Pres
				BitFail,
				hfs2000c01v1R2lIn6Pres
				BitFail,
				hfs2000c01v1R2lIn7Pres
				BitFail,
				hfs2000c01v1R2lIn8Pres
				BitFail,
				hfs2000c01v1R2lIn9Pres
				BitFail,
				hfs2000c01v1R2lIn10Pres
				BitFail,
				hfs2000c01v1R2lIn11Pres
				BitFail,
				hfs2000c01v1R2lIn12Pres
				BitFail,
				hfs2000c01v1R2lIn13Pres
				BitFail,
				hfs2000c01v1R2lIn14Pres
				BitFail,
				hfs2000c01v1R2lIn15Pres
				BitFail,
				hfs2000c01v1R2lIn16Pres
				BitFail,
				hfs2000c01v1SerialNo
				SerialNo
			 }

		-- 1.3.6.1.4.1.10106.3.101291.1.1.1
		hfs2000c01v1Index OBJECT-TYPE
			SYNTAX ModuleIndex
			MAX-ACCESS read-only
			STATUS current
			DESCRIPTION
				"Index of HFS2000C01V1 Table"
		::= { hfs2000c01v1Entry 1 }

		-- 1.3.6.1.4.1.10106.3.101291.1.1.3
		hfs2000c01v1SynchroMode OBJECT-TYPE
			SYNTAX Bit0Fra1Lin
			MAX-ACCESS read-write
			STATUS current
			DESCRIPTION
				"Allows selecting the synchronizing mode"
		::= { hfs2000c01v1Entry 3 }

		-- 1.3.6.1.4.1.10106.3.101291.1.1.5
		hfs2000c01v1FailMode OBJECT-TYPE
			SYNTAX Bit0Fre1Blk
			MAX-ACCESS read-write
			STATUS current
			DESCRIPTION
				"Allows selecting the output video signal if the input fails"
		::= { hfs2000c01v1Entry 5 }

		-- 1.3.6.1.4.1.10106.3.101291.1.1.7
		hfs2000c01v1VbiMode OBJECT-TYPE
			SYNTAX Bit0Pas1Bnk
			MAX-ACCESS read-write
			STATUS current
			DESCRIPTION
				"Allows selecting if the VBI is blanked"
		::= { hfs2000c01v1Entry 7 }

		-- 1.3.6.1.4.1.10106.3.101291.1.1.9
		hfs2000c01v1DelayMode OBJECT-TYPE
			SYNTAX Bit0Syn1De2
			MAX-ACCESS read-write
			STATUS current
			DESCRIPTION
				"Allows selecting the operating mode"
		::= { hfs2000c01v1Entry 9 }

		-- 1.3.6.1.4.1.10106.3.101291.1.1.11
		hfs2000c01v1HDelay OBJECT-TYPE
			SYNTAX DelayPixel5
			MAX-ACCESS read-write
			STATUS current
			DESCRIPTION
				"Allows adjusting the video horizontal delay"
		::= { hfs2000c01v1Entry 11 }

		-- 1.3.6.1.4.1.10106.3.101291.1.1.13
		hfs2000c01v1FrameDelay OBJECT-TYPE
			SYNTAX DelayFram4
			MAX-ACCESS read-write
			STATUS current
			DESCRIPTION
				"Allows adjusting the frame delay"
		::= { hfs2000c01v1Entry 13 }

		-- 1.3.6.1.4.1.10106.3.101291.1.1.15
		hfs2000c01v1VDelay OBJECT-TYPE
			SYNTAX DelayLines2
			MAX-ACCESS read-write
			STATUS current
			DESCRIPTION
				"Allows adjusting the video vertical delay"
		::= { hfs2000c01v1Entry 15 }

		-- 1.3.6.1.4.1.10106.3.101291.1.1.17
		hfs2000c01v1LumaGain OBJECT-TYPE
			SYNTAX GainLin1
			MAX-ACCESS read-write
			STATUS current
			DESCRIPTION
				"Allows adjusting the luma gain"
		::= { hfs2000c01v1Entry 17 }

		-- 1.3.6.1.4.1.10106.3.101291.1.1.19
		hfs2000c01v1ChromaGain OBJECT-TYPE
			SYNTAX GainLin1
			MAX-ACCESS read-write
			STATUS current
			DESCRIPTION
				"Allows adjusting the chorma gain"
		::= { hfs2000c01v1Entry 19 }

		-- 1.3.6.1.4.1.10106.3.101291.1.1.21
		hfs2000c01v1BlackOffset OBJECT-TYPE
			SYNTAX BlackOffset1
			MAX-ACCESS read-write
			STATUS current
			DESCRIPTION
				"Allows adjusting the black offset"
		::= { hfs2000c01v1Entry 21 }

		-- 1.3.6.1.4.1.10106.3.101291.1.1.23
		hfs2000c01v1Bits OBJECT-TYPE
			SYNTAX Bit020124
			MAX-ACCESS read-write
			STATUS current
			DESCRIPTION
				"Allows selecting the number of bits"
		::= { hfs2000c01v1Entry 23 }

		-- 1.3.6.1.4.1.10106.3.101291.1.1.25
		hfs2000c01v1Grp1P0lSrc OBJECT-TYPE
			SYNTAX AudioSource
			MAX-ACCESS read-write
			STATUS current
			DESCRIPTION
				"Group 1 pair 0 L source"
		::= { hfs2000c01v1Entry 25 }

		-- 1.3.6.1.4.1.10106.3.101291.1.1.27
		hfs2000c01v1Grp1P0rSrc OBJECT-TYPE
			SYNTAX AudioSource
			MAX-ACCESS read-write
			STATUS current
			DESCRIPTION
				"Group 1 pair 0 R source"
		::= { hfs2000c01v1Entry 27 }

		-- 1.3.6.1.4.1.10106.3.101291.1.1.29
		hfs2000c01v1Grp1P1lSrc OBJECT-TYPE
			SYNTAX AudioSource
			MAX-ACCESS read-write
			STATUS current
			DESCRIPTION
				"Group 1 pair 1 L source"
		::= { hfs2000c01v1Entry 29 }

		-- 1.3.6.1.4.1.10106.3.101291.1.1.31
		hfs2000c01v1Grp1P1rSrc OBJECT-TYPE
			SYNTAX AudioSource
			MAX-ACCESS read-write
			STATUS current
			DESCRIPTION
				"Group 1 pair 1 R source"
		::= { hfs2000c01v1Entry 31 }

		-- 1.3.6.1.4.1.10106.3.101291.1.1.33
		hfs2000c01v1Grp1P0l OBJECT-TYPE
			SYNTAX AudioMxInput7
			MAX-ACCESS read-write
			STATUS current
			DESCRIPTION
				"Allows selecting the audio embedded in group 1 pair 0 L"
		::= { hfs2000c01v1Entry 33 }

		-- 1.3.6.1.4.1.10106.3.101291.1.1.35
		hfs2000c01v1Grp1P0r OBJECT-TYPE
			SYNTAX AudioMxInput7
			MAX-ACCESS read-write
			STATUS current
			DESCRIPTION
				"Allows selecting the audio embedded in group 1 pair 0 R"
		::= { hfs2000c01v1Entry 35 }

		-- 1.3.6.1.4.1.10106.3.101291.1.1.37
		hfs2000c01v1Grp1P1l OBJECT-TYPE
			SYNTAX AudioMxInput7
			MAX-ACCESS read-write
			STATUS current
			DESCRIPTION
				"Allows selecting the audio embedded in group 1 pair 1 L"
		::= { hfs2000c01v1Entry 37 }

		-- 1.3.6.1.4.1.10106.3.101291.1.1.39
		hfs2000c01v1Grp1P1r OBJECT-TYPE
			SYNTAX AudioMxInput7
			MAX-ACCESS read-write
			STATUS current
			DESCRIPTION
				"Allows selecting the audio embedded in group 1 pair 1 R"
		::= { hfs2000c01v1Entry 39 }

		-- 1.3.6.1.4.1.10106.3.101291.1.1.41
		hfs2000c01v1Grp2P0lSrc OBJECT-TYPE
			SYNTAX AudioSource
			MAX-ACCESS read-write
			STATUS current
			DESCRIPTION
				"Group 2 pair 0 L source"
		::= { hfs2000c01v1Entry 41 }

		-- 1.3.6.1.4.1.10106.3.101291.1.1.43
		hfs2000c01v1Grp2P0rSrc OBJECT-TYPE
			SYNTAX AudioSource
			MAX-ACCESS read-write
			STATUS current
			DESCRIPTION
				"Group 2 pair 0 R source"
		::= { hfs2000c01v1Entry 43 }

		-- 1.3.6.1.4.1.10106.3.101291.1.1.45
		hfs2000c01v1Grp2P1lSrc OBJECT-TYPE
			SYNTAX AudioSource
			MAX-ACCESS read-write
			STATUS current
			DESCRIPTION
				"Group 2 pair 1 L source"
		::= { hfs2000c01v1Entry 45 }

		-- 1.3.6.1.4.1.10106.3.101291.1.1.47
		hfs2000c01v1Grp2P1rSrc OBJECT-TYPE
			SYNTAX AudioSource
			MAX-ACCESS read-write
			STATUS current
			DESCRIPTION
				"Group 2 pair 1 R source"
		::= { hfs2000c01v1Entry 47 }

		-- 1.3.6.1.4.1.10106.3.101291.1.1.49
		hfs2000c01v1Grp2P0l OBJECT-TYPE
			SYNTAX AudioMxInput7
			MAX-ACCESS read-write
			STATUS current
			DESCRIPTION
				"Allows selecting the audio embedded in group 2 pair 0 L"
		::= { hfs2000c01v1Entry 49 }

		-- 1.3.6.1.4.1.10106.3.101291.1.1.51
		hfs2000c01v1Grp2P0r OBJECT-TYPE
			SYNTAX AudioMxInput7
			MAX-ACCESS read-write
			STATUS current
			DESCRIPTION
				"Allows selecting the audio embedded in group 2 pair 0 R"
		::= { hfs2000c01v1Entry 51 }

		-- 1.3.6.1.4.1.10106.3.101291.1.1.53
		hfs2000c01v1Grp2P1l OBJECT-TYPE
			SYNTAX AudioMxInput7
			MAX-ACCESS read-write
			STATUS current
			DESCRIPTION
				"Allows selecting the audio embedded in group 2 pair 1 L"
		::= { hfs2000c01v1Entry 53 }

		-- 1.3.6.1.4.1.10106.3.101291.1.1.55
		hfs2000c01v1Grp2P1r OBJECT-TYPE
			SYNTAX AudioMxInput7
			MAX-ACCESS read-write
			STATUS current
			DESCRIPTION
				"Allows selecting the audio embedded in group 2 pair 1 R"
		::= { hfs2000c01v1Entry 55 }

		-- 1.3.6.1.4.1.10106.3.101291.1.1.57
		hfs2000c01v1Grp3P0lSrc OBJECT-TYPE
			SYNTAX AudioSource
			MAX-ACCESS read-write
			STATUS current
			DESCRIPTION
				"Group 3 pair 0 L source"
		::= { hfs2000c01v1Entry 57 }

		-- 1.3.6.1.4.1.10106.3.101291.1.1.59
		hfs2000c01v1Grp3P0rSrc OBJECT-TYPE
			SYNTAX AudioSource
			MAX-ACCESS read-write
			STATUS current
			DESCRIPTION
				"Group 3 pair 0 R source"
		::= { hfs2000c01v1Entry 59 }

		-- 1.3.6.1.4.1.10106.3.101291.1.1.61
		hfs2000c01v1Grp3P1lSrc OBJECT-TYPE
			SYNTAX AudioSource
			MAX-ACCESS read-write
			STATUS current
			DESCRIPTION
				"Group 3 pair 1 L source"
		::= { hfs2000c01v1Entry 61 }

		-- 1.3.6.1.4.1.10106.3.101291.1.1.63
		hfs2000c01v1Grp3P1rSrc OBJECT-TYPE
			SYNTAX AudioSource
			MAX-ACCESS read-write
			STATUS current
			DESCRIPTION
				"Group 3 pair 1 R source"
		::= { hfs2000c01v1Entry 63 }

		-- 1.3.6.1.4.1.10106.3.101291.1.1.65
		hfs2000c01v1Grp3P0l OBJECT-TYPE
			SYNTAX AudioMxInput7
			MAX-ACCESS read-write
			STATUS current
			DESCRIPTION
				"Allows selecting the audio embedded in group 3 pair 0 L"
		::= { hfs2000c01v1Entry 65 }

		-- 1.3.6.1.4.1.10106.3.101291.1.1.67
		hfs2000c01v1Grp3P0r OBJECT-TYPE
			SYNTAX AudioMxInput7
			MAX-ACCESS read-write
			STATUS current
			DESCRIPTION
				"Allows selecting the audio embedded in group 3 pair 0 R"
		::= { hfs2000c01v1Entry 67 }

		-- 1.3.6.1.4.1.10106.3.101291.1.1.69
		hfs2000c01v1Grp3P1l OBJECT-TYPE
			SYNTAX AudioMxInput7
			MAX-ACCESS read-write
			STATUS current
			DESCRIPTION
				"Allows selecting the audio embedded in group 3 pair 1 L"
		::= { hfs2000c01v1Entry 69 }

		-- 1.3.6.1.4.1.10106.3.101291.1.1.71
		hfs2000c01v1Grp3P1r OBJECT-TYPE
			SYNTAX AudioMxInput7
			MAX-ACCESS read-write
			STATUS current
			DESCRIPTION
				"Allows selecting the audio embedded in group 3 pair 1 R"
		::= { hfs2000c01v1Entry 71 }

		-- 1.3.6.1.4.1.10106.3.101291.1.1.73
		hfs2000c01v1Grp4P0lSrc OBJECT-TYPE
			SYNTAX AudioSource
			MAX-ACCESS read-write
			STATUS current
			DESCRIPTION
				"Group 4 pair 0 L source"
		::= { hfs2000c01v1Entry 73 }

		-- 1.3.6.1.4.1.10106.3.101291.1.1.75
		hfs2000c01v1Grp4P0rSrc OBJECT-TYPE
			SYNTAX AudioSource
			MAX-ACCESS read-write
			STATUS current
			DESCRIPTION
				"Group 4 pair 0 R source"
		::= { hfs2000c01v1Entry 75 }

		-- 1.3.6.1.4.1.10106.3.101291.1.1.77
		hfs2000c01v1Grp4P1lSrc OBJECT-TYPE
			SYNTAX AudioSource
			MAX-ACCESS read-write
			STATUS current
			DESCRIPTION
				"Group 4 pair 1 L source"
		::= { hfs2000c01v1Entry 77 }

		-- 1.3.6.1.4.1.10106.3.101291.1.1.79
		hfs2000c01v1Grp4P1rSrc OBJECT-TYPE
			SYNTAX AudioSource
			MAX-ACCESS read-write
			STATUS current
			DESCRIPTION
				"Group 4 pair 1 R source"
		::= { hfs2000c01v1Entry 79 }

		-- 1.3.6.1.4.1.10106.3.101291.1.1.81
		hfs2000c01v1Grp4P0l OBJECT-TYPE
			SYNTAX AudioMxInput7
			MAX-ACCESS read-write
			STATUS current
			DESCRIPTION
				"Allows selecting the audio embedded in group 4 pair 0 L"
		::= { hfs2000c01v1Entry 81 }

		-- 1.3.6.1.4.1.10106.3.101291.1.1.83
		hfs2000c01v1Grp4P0r OBJECT-TYPE
			SYNTAX AudioMxInput7
			MAX-ACCESS read-write
			STATUS current
			DESCRIPTION
				"Allows selecting the audio embedded in group 4 pair 0 R"
		::= { hfs2000c01v1Entry 83 }

		-- 1.3.6.1.4.1.10106.3.101291.1.1.85
		hfs2000c01v1Grp4P1l OBJECT-TYPE
			SYNTAX AudioMxInput7
			MAX-ACCESS read-write
			STATUS current
			DESCRIPTION
				"Allows selecting the audio embedded in group 4 pair 1 L"
		::= { hfs2000c01v1Entry 85 }

		-- 1.3.6.1.4.1.10106.3.101291.1.1.87
		hfs2000c01v1Grp4P1r OBJECT-TYPE
			SYNTAX AudioMxInput7
			MAX-ACCESS read-write
			STATUS current
			DESCRIPTION
				"Allows selecting the audio embedded in group 4 pair 1 R"
		::= { hfs2000c01v1Entry 87 }

		-- 1.3.6.1.4.1.10106.3.101291.1.1.89
		hfs2000c01v1NoSig OBJECT-TYPE
			SYNTAX BitFail
			MAX-ACCESS read-only
			STATUS current
			DESCRIPTION
				"Indicates SDI signal fail"
		::= { hfs2000c01v1Entry 89 }

		-- 1.3.6.1.4.1.10106.3.101291.1.1.90
		hfs2000c01v1NoSigTrapEnable OBJECT-TYPE
			SYNTAX AlarmEnable
			MAX-ACCESS read-write
			STATUS current
			DESCRIPTION
				"Indicates SDI signal fail Trap Enable"
		::= { hfs2000c01v1Entry 90 }

		-- 1.3.6.1.4.1.10106.3.101291.1.1.91
		hfs2000c01v1Unlock OBJECT-TYPE
			SYNTAX BitFail
			MAX-ACCESS read-only
			STATUS current
			DESCRIPTION
				"Indicates signal unlock"
		::= { hfs2000c01v1Entry 91 }

		-- 1.3.6.1.4.1.10106.3.101291.1.1.92
		hfs2000c01v1UnlockTrapEnable OBJECT-TYPE
			SYNTAX AlarmEnable
			MAX-ACCESS read-write
			STATUS current
			DESCRIPTION
				"Indicates signal unlock Trap Enable"
		::= { hfs2000c01v1Entry 92 }

		-- 1.3.6.1.4.1.10106.3.101291.1.1.93
		hfs2000c01v1EdhCrc OBJECT-TYPE
			SYNTAX BitFail
			MAX-ACCESS read-only
			STATUS current
			DESCRIPTION
				"Indicates presence of EDH/CRC errors"
		::= { hfs2000c01v1Entry 93 }

		-- 1.3.6.1.4.1.10106.3.101291.1.1.94
		hfs2000c01v1EdhCrcTrapEnable OBJECT-TYPE
			SYNTAX AlarmEnable
			MAX-ACCESS read-write
			STATUS current
			DESCRIPTION
				"Indicates presence of EDH/CRC errors Trap Enable"
		::= { hfs2000c01v1Entry 94 }

		-- 1.3.6.1.4.1.10106.3.101291.1.1.95
		hfs2000c01v1NoRef OBJECT-TYPE
			SYNTAX BitFail
			MAX-ACCESS read-only
			STATUS current
			DESCRIPTION
				"Indicates reference signal fail"
		::= { hfs2000c01v1Entry 95 }

		-- 1.3.6.1.4.1.10106.3.101291.1.1.96
		hfs2000c01v1NoRefTrapEnable OBJECT-TYPE
			SYNTAX AlarmEnable
			MAX-ACCESS read-write
			STATUS current
			DESCRIPTION
				"Indicates reference signal fail Trap Enable"
		::= { hfs2000c01v1Entry 96 }

		-- 1.3.6.1.4.1.10106.3.101291.1.1.97
		hfs2000c01v1RefUnlock OBJECT-TYPE
			SYNTAX BitFail
			MAX-ACCESS read-only
			STATUS current
			DESCRIPTION
				"Indicates reference signal unlock fail"
		::= { hfs2000c01v1Entry 97 }

		-- 1.3.6.1.4.1.10106.3.101291.1.1.98
		hfs2000c01v1RefUnlockTrapEnable OBJECT-TYPE
			SYNTAX AlarmEnable
			MAX-ACCESS read-write
			STATUS current
			DESCRIPTION
				"Indicates reference signal unlock fail Trap Enable"
		::= { hfs2000c01v1Entry 98 }

		-- 1.3.6.1.4.1.10106.3.101291.1.1.99
		hfs2000c01v1InputFormat OBJECT-TYPE
			SYNTAX SdiHd3gFmt3
			MAX-ACCESS read-only
			STATUS current
			DESCRIPTION
				"Indicates the reference signal format"
		::= { hfs2000c01v1Entry 99 }

		-- 1.3.6.1.4.1.10106.3.101291.1.1.101
		hfs2000c01v1SdiFormat OBJECT-TYPE
			SYNTAX SdiHd3gFmt3
			MAX-ACCESS read-only
			STATUS current
			DESCRIPTION
				"Indicates the SDI input format"
		::= { hfs2000c01v1Entry 101 }

		-- 1.3.6.1.4.1.10106.3.101291.1.1.103
		hfs2000c01v1SigDelay OBJECT-TYPE
			SYNTAX DelayX20Us
			MAX-ACCESS read-only
			STATUS current
			DESCRIPTION
				"Indicates the input to output delay"
		::= { hfs2000c01v1Entry 103 }

		-- 1.3.6.1.4.1.10106.3.101291.1.1.105
		hfs2000c01v1Grp1Pres OBJECT-TYPE
			SYNTAX Bit0No1Yes
			MAX-ACCESS read-only
			STATUS current
			DESCRIPTION
				"Group 1 presence"
		::= { hfs2000c01v1Entry 105 }

		-- 1.3.6.1.4.1.10106.3.101291.1.1.107
		hfs2000c01v1Grp2Pres OBJECT-TYPE
			SYNTAX Bit0No1Yes
			MAX-ACCESS read-only
			STATUS current
			DESCRIPTION
				"Group 2 presence"
		::= { hfs2000c01v1Entry 107 }

		-- 1.3.6.1.4.1.10106.3.101291.1.1.109
		hfs2000c01v1Grp3Pres OBJECT-TYPE
			SYNTAX Bit0No1Yes
			MAX-ACCESS read-only
			STATUS current
			DESCRIPTION
				"Group 3 presence"
		::= { hfs2000c01v1Entry 109 }

		-- 1.3.6.1.4.1.10106.3.101291.1.1.111
		hfs2000c01v1Grp4Pres OBJECT-TYPE
			SYNTAX Bit0No1Yes
			MAX-ACCESS read-only
			STATUS current
			DESCRIPTION
				"Group 4 presence"
		::= { hfs2000c01v1Entry 111 }

		-- 1.3.6.1.4.1.10106.3.101291.1.1.113
		hfs2000c01v1Grp1P0Err OBJECT-TYPE
			SYNTAX BitFail
			MAX-ACCESS read-only
			STATUS current
			DESCRIPTION
				"SDI A group 1 pair 0 fail"
		::= { hfs2000c01v1Entry 113 }

		-- 1.3.6.1.4.1.10106.3.101291.1.1.115
		hfs2000c01v1Grp1P1Err OBJECT-TYPE
			SYNTAX BitFail
			MAX-ACCESS read-only
			STATUS current
			DESCRIPTION
				"SDI A group 1 pair 1 fail"
		::= { hfs2000c01v1Entry 115 }

		-- 1.3.6.1.4.1.10106.3.101291.1.1.117
		hfs2000c01v1Grp2P0Err OBJECT-TYPE
			SYNTAX BitFail
			MAX-ACCESS read-only
			STATUS current
			DESCRIPTION
				"SDI A group 2 pair 0 fail"
		::= { hfs2000c01v1Entry 117 }

		-- 1.3.6.1.4.1.10106.3.101291.1.1.119
		hfs2000c01v1Grp2P1Err OBJECT-TYPE
			SYNTAX BitFail
			MAX-ACCESS read-only
			STATUS current
			DESCRIPTION
				"SDI A group 2 pair 1 fail"
		::= { hfs2000c01v1Entry 119 }

		-- 1.3.6.1.4.1.10106.3.101291.1.1.121
		hfs2000c01v1Grp3P0Err OBJECT-TYPE
			SYNTAX BitFail
			MAX-ACCESS read-only
			STATUS current
			DESCRIPTION
				"SDI A group 3 pair 0 fail"
		::= { hfs2000c01v1Entry 121 }

		-- 1.3.6.1.4.1.10106.3.101291.1.1.123
		hfs2000c01v1Grp3P1Err OBJECT-TYPE
			SYNTAX BitFail
			MAX-ACCESS read-only
			STATUS current
			DESCRIPTION
				"SDI A group 3 pair 1 fail"
		::= { hfs2000c01v1Entry 123 }

		-- 1.3.6.1.4.1.10106.3.101291.1.1.125
		hfs2000c01v1Grp4P0Err OBJECT-TYPE
			SYNTAX BitFail
			MAX-ACCESS read-only
			STATUS current
			DESCRIPTION
				"SDI A group 4 pair 0 fail"
		::= { hfs2000c01v1Entry 125 }

		-- 1.3.6.1.4.1.10106.3.101291.1.1.127
		hfs2000c01v1Grp4P1Err OBJECT-TYPE
			SYNTAX BitFail
			MAX-ACCESS read-only
			STATUS current
			DESCRIPTION
				"SDI A group 4 pair 1 fail"
		::= { hfs2000c01v1Entry 127 }

		-- 1.3.6.1.4.1.10106.3.101291.1.1.129
		hfs2000c01v1R2lIn1Pres OBJECT-TYPE
			SYNTAX BitFail
			MAX-ACCESS read-only
			STATUS current
			DESCRIPTION
				"R2L IN channel 1 fail"
		::= { hfs2000c01v1Entry 129 }

		-- 1.3.6.1.4.1.10106.3.101291.1.1.131
		hfs2000c01v1R2lIn2Pres OBJECT-TYPE
			SYNTAX BitFail
			MAX-ACCESS read-only
			STATUS current
			DESCRIPTION
				"R2L IN channel 2 fail"
		::= { hfs2000c01v1Entry 131 }

		-- 1.3.6.1.4.1.10106.3.101291.1.1.133
		hfs2000c01v1R2lIn3Pres OBJECT-TYPE
			SYNTAX BitFail
			MAX-ACCESS read-only
			STATUS current
			DESCRIPTION
				"R2L IN channel 3 fail"
		::= { hfs2000c01v1Entry 133 }

		-- 1.3.6.1.4.1.10106.3.101291.1.1.135
		hfs2000c01v1R2lIn4Pres OBJECT-TYPE
			SYNTAX BitFail
			MAX-ACCESS read-only
			STATUS current
			DESCRIPTION
				"R2L IN channel 4 fail"
		::= { hfs2000c01v1Entry 135 }

		-- 1.3.6.1.4.1.10106.3.101291.1.1.137
		hfs2000c01v1R2lIn5Pres OBJECT-TYPE
			SYNTAX BitFail
			MAX-ACCESS read-only
			STATUS current
			DESCRIPTION
				"R2L IN channel 5 fail"
		::= { hfs2000c01v1Entry 137 }

		-- 1.3.6.1.4.1.10106.3.101291.1.1.139
		hfs2000c01v1R2lIn6Pres OBJECT-TYPE
			SYNTAX BitFail
			MAX-ACCESS read-only
			STATUS current
			DESCRIPTION
				"R2L IN channel 6 fail"
		::= { hfs2000c01v1Entry 139 }

		-- 1.3.6.1.4.1.10106.3.101291.1.1.141
		hfs2000c01v1R2lIn7Pres OBJECT-TYPE
			SYNTAX BitFail
			MAX-ACCESS read-only
			STATUS current
			DESCRIPTION
				"R2L IN channel 7 fail"
		::= { hfs2000c01v1Entry 141 }

		-- 1.3.6.1.4.1.10106.3.101291.1.1.143
		hfs2000c01v1R2lIn8Pres OBJECT-TYPE
			SYNTAX BitFail
			MAX-ACCESS read-only
			STATUS current
			DESCRIPTION
				"R2L IN channel 8 fail"
		::= { hfs2000c01v1Entry 143 }

		-- 1.3.6.1.4.1.10106.3.101291.1.1.145
		hfs2000c01v1R2lIn9Pres OBJECT-TYPE
			SYNTAX BitFail
			MAX-ACCESS read-only
			STATUS current
			DESCRIPTION
				"R2L IN channel 9 fail"
		::= { hfs2000c01v1Entry 145 }

		-- 1.3.6.1.4.1.10106.3.101291.1.1.147
		hfs2000c01v1R2lIn10Pres OBJECT-TYPE
			SYNTAX BitFail
			MAX-ACCESS read-only
			STATUS current
			DESCRIPTION
				"R2L IN channel 10 fail"
		::= { hfs2000c01v1Entry 147 }

		-- 1.3.6.1.4.1.10106.3.101291.1.1.149
		hfs2000c01v1R2lIn11Pres OBJECT-TYPE
			SYNTAX BitFail
			MAX-ACCESS read-only
			STATUS current
			DESCRIPTION
				"R2L IN channel 11 fail"
		::= { hfs2000c01v1Entry 149 }

		-- 1.3.6.1.4.1.10106.3.101291.1.1.151
		hfs2000c01v1R2lIn12Pres OBJECT-TYPE
			SYNTAX BitFail
			MAX-ACCESS read-only
			STATUS current
			DESCRIPTION
				"R2L IN channel 12 fail"
		::= { hfs2000c01v1Entry 151 }

		-- 1.3.6.1.4.1.10106.3.101291.1.1.153
		hfs2000c01v1R2lIn13Pres OBJECT-TYPE
			SYNTAX BitFail
			MAX-ACCESS read-only
			STATUS current
			DESCRIPTION
				"R2L IN channel 13 fail"
		::= { hfs2000c01v1Entry 153 }

		-- 1.3.6.1.4.1.10106.3.101291.1.1.155
		hfs2000c01v1R2lIn14Pres OBJECT-TYPE
			SYNTAX BitFail
			MAX-ACCESS read-only
			STATUS current
			DESCRIPTION
				"R2L IN channel 14 fail"
		::= { hfs2000c01v1Entry 155 }

		-- 1.3.6.1.4.1.10106.3.101291.1.1.157
		hfs2000c01v1R2lIn15Pres OBJECT-TYPE
			SYNTAX BitFail
			MAX-ACCESS read-only
			STATUS current
			DESCRIPTION
				"R2L IN channel 15 fail"
		::= { hfs2000c01v1Entry 157 }

		-- 1.3.6.1.4.1.10106.3.101291.1.1.159
		hfs2000c01v1R2lIn16Pres OBJECT-TYPE
			SYNTAX BitFail
			MAX-ACCESS read-only
			STATUS current
			DESCRIPTION
				"R2L IN channel 16 fail"
		::= { hfs2000c01v1Entry 159 }

		-- 1.3.6.1.4.1.10106.3.101291.1.1.161
		hfs2000c01v1SerialNo OBJECT-TYPE
			SYNTAX SerialNo
			MAX-ACCESS read-only
			STATUS current
			DESCRIPTION
				"Serial number"
		::= { hfs2000c01v1Entry 161 }

		-- 1.3.6.1.4.1.10106.3.471001
		htc3000c01v1 OBJECT IDENTIFIER ::= { albalaProducts 471001 }

		-- 1.3.6.1.4.1.10106.3.471001.1
		htc3000c01v1Table  OBJECT-TYPE
			SYNTAX SEQUENCE OF Htc3000c01v1Entry
			MAX-ACCESS not-accessible
			STATUS current
			DESCRIPTION
				"Module  HTC3000C01V1 Table"
			::= { htc3000c01v1 1 }

		-- 1.3.6.1.4.1.10106.3.471001.1.1
		htc3000c01v1Entry  OBJECT-TYPE
			SYNTAX Htc3000c01v1Entry
			MAX-ACCESS not-accessible
			STATUS current
			DESCRIPTION
				"Module HTC3000C01V1 Entry"
			INDEX { htc3000c01v1Index }
			::= { htc3000c01v1Table 1 }

			Htc3000c01v1Entry ::=
			SEQUENCE {
				htc3000c01v1Index
				ModuleIndex,
				htc3000c01v1ActivePreset
				Preset16Active,
				htc3000c01v1LoadPreset
				Preset16Load,
				htc3000c01v1SavePreset
				Preset16Save,
				htc3000c01v1AnaRefFmt
				SdiHd3gFmt6,
				htc3000c01v1DelayMode
				V0SyncV2DmAu,
				htc3000c01v1SynchroMode
				Bit0Fra1Lin,
				htc3000c01v1FailMode
				Bit0Fre1Blk,
				htc3000c01v1InitFmt
				SdiHd3gFmt6,
				htc3000c01v1GenEn
				BitMask,
				htc3000c01v1HDelay
				DelayPixel5,
				htc3000c01v1VDelay
				DelayLines2,
				htc3000c01v1ModeTc
				TcModeCombo,
				htc3000c01v1SrcTc
				TcSource,
				htc3000c01v1DropFr
				BitMask,
				htc3000c01v1Bgf
				BgfBits,
				htc3000c01v1EnDlsave
				BitMask,
				htc3000c01v1DateFormat
				DateFmt,
				htc3000c01v1DvitcIns
				BitMask,
				htc3000c01v1AtcIns
				BitMask,
				htc3000c01v1AtcType
				VitcLtc,
				htc3000c01v1OsdIns
				BitMask,
				htc3000c01v1OsdPosition
				ClockPosition,
				htc3000c01v1AuxGen
				CodeGen,
				htc3000c01v1ClockFormat
				ClockFormat,
				htc3000c01v1ClockAmPm
				ClockAmPm,
				htc3000c01v1ClockSize
				ClockSize,
				htc3000c01v1LevelPips
				LevelDbfsD,
				htc3000c01v1MediasGen
				BitMask,
				htc3000c01v1FreqPips
				FrqGen,
				htc3000c01v1NPipsHour
				Uint4,
				htc3000c01v1NPipsHalf
				Uint4,
				htc3000c01v1ShortPerHour
				TimeX100Ms,
				htc3000c01v1ShortPerHalf
				TimeX100Ms,
				htc3000c01v1LongPerHour
				TimeX100Ms,
				htc3000c01v1LongPerHalf
				TimeX100Ms,
				htc3000c01v1SumMonthSt
				Month,
				htc3000c01v1SumWeekSt
				WeekOfMonth,
				htc3000c01v1SumWDaySt
				Day,
				htc3000c01v1SumHourSt
				TimeH1,
				htc3000c01v1SumHourOffset
				Int8,
				htc3000c01v1WinMonthSt
				Month,
				htc3000c01v1WinWeekSt
				WeekOfMonth,
				htc3000c01v1WinWDaySt
				Day,
				htc3000c01v1WinHourSt
				TimeH1,
				htc3000c01v1WinHourOffset
				Int8,
				htc3000c01v1RefAbsent
				BitFail,
				htc3000c01v1RefAbsentTrapEnable
				AlarmEnable,
				htc3000c01v1RefUnlock
				BitFail,
				htc3000c01v1RefUnlockTrapEnable
				AlarmEnable,
				htc3000c01v1NoSignalMain
				BitFail,
				htc3000c01v1NoSignalMainTrapEnable
				AlarmEnable,
				htc3000c01v1UnlockMain
				BitFail,
				htc3000c01v1UnlockMainTrapEnable
				AlarmEnable,
				htc3000c01v1EdhErrorMain
				BitFail,
				htc3000c01v1EdhErrorMainTrapEnable
				AlarmEnable,
				htc3000c01v1NoSignalAux
				BitFail,
				htc3000c01v1NoSignalAuxTrapEnable
				AlarmEnable,
				htc3000c01v1UnlockAux
				BitFail,
				htc3000c01v1UnlockAuxTrapEnable
				AlarmEnable,
				htc3000c01v1EdhErrorAux
				BitFail,
				htc3000c01v1EdhErrorAuxTrapEnable
				AlarmEnable,
				htc3000c01v1IncompFmt
				BitFail,
				htc3000c01v1IncompFmtTrapEnable
				AlarmEnable,
				htc3000c01v1TcFail
				BitFail,
				htc3000c01v1TcFailTrapEnable
				AlarmEnable,
				htc3000c01v1FormatRef
				SdiHd3gFmt7,
				htc3000c01v1FormatMainIn
				SdiHd3gFmt7,
				htc3000c01v1FormatAuxIn
				SdiHd3gFmt7,
				htc3000c01v1FormatMainTx
				SdiHd3gFmt7,
				htc3000c01v1SigDelay
				DelayX20Us,
				htc3000c01v1DvitcPres
				BitFailN,
				htc3000c01v1AtcVitcPres
				BitFailN,
				htc3000c01v1AtcLtcPres
				BitFailN,
				htc3000c01v1LtcPres
				BitFailN,
				htc3000c01v1BgfSt
				BgfBits,
				htc3000c01v1DropFSt
				Bit0No1Yes,
				htc3000c01v1ColorFSt
				Bit0No1Yes,
				htc3000c01v1SerialNo
				SerialNo,
				htc3000c01v1DateFmtRx
				DateFmt,
				htc3000c01v1EnDateGen
				BitMask
			 }

		-- 1.3.6.1.4.1.10106.3.101291.1.1.1
		htc3000c01v1Index OBJECT-TYPE
			SYNTAX ModuleIndex
			MAX-ACCESS read-only
			STATUS current
			DESCRIPTION
				"Index of HTC3000C01V1 Table"
		::= { htc3000c01v1Entry 1 }

		-- 1.3.6.1.4.1.10106.3.101291.1.1.3
		htc3000c01v1ActivePreset OBJECT-TYPE
			SYNTAX Preset16Active
			MAX-ACCESS read-only
			STATUS current
			DESCRIPTION
				"Shows the active preset"
		::= { htc3000c01v1Entry 3 }

		-- 1.3.6.1.4.1.10106.3.101291.1.1.5
		htc3000c01v1LoadPreset OBJECT-TYPE
			SYNTAX Preset16Load
			MAX-ACCESS read-write
			STATUS current
			DESCRIPTION
				"Allows loading a preset"
		::= { htc3000c01v1Entry 5 }

		-- 1.3.6.1.4.1.10106.3.101291.1.1.7
		htc3000c01v1SavePreset OBJECT-TYPE
			SYNTAX Preset16Save
			MAX-ACCESS read-write
			STATUS current
			DESCRIPTION
				"Allows saving a preset"
		::= { htc3000c01v1Entry 7 }

		-- 1.3.6.1.4.1.10106.3.101291.1.1.9
		htc3000c01v1AnaRefFmt OBJECT-TYPE
			SYNTAX SdiHd3gFmt6
			MAX-ACCESS read-write
			STATUS current
			DESCRIPTION
				"Analog reference input format"
		::= { htc3000c01v1Entry 9 }

		-- 1.3.6.1.4.1.10106.3.101291.1.1.11
		htc3000c01v1DelayMode OBJECT-TYPE
			SYNTAX V0SyncV2DmAu
			MAX-ACCESS read-write
			STATUS current
			DESCRIPTION
				"Allows selecting the operating mode"
		::= { htc3000c01v1Entry 11 }

		-- 1.3.6.1.4.1.10106.3.101291.1.1.13
		htc3000c01v1SynchroMode OBJECT-TYPE
			SYNTAX Bit0Fra1Lin
			MAX-ACCESS read-write
			STATUS current
			DESCRIPTION
				"Allows selecting the synchronizing mode"
		::= { htc3000c01v1Entry 13 }

		-- 1.3.6.1.4.1.10106.3.101291.1.1.15
		htc3000c01v1FailMode OBJECT-TYPE
			SYNTAX Bit0Fre1Blk
			MAX-ACCESS read-write
			STATUS current
			DESCRIPTION
				"Allows selecting the output video signal if the input fails"
		::= { htc3000c01v1Entry 15 }

		-- 1.3.6.1.4.1.10106.3.101291.1.1.17
		htc3000c01v1InitFmt OBJECT-TYPE
			SYNTAX SdiHd3gFmt6
			MAX-ACCESS read-write
			STATUS current
			DESCRIPTION
				"Initial or generator format"
		::= { htc3000c01v1Entry 17 }

		-- 1.3.6.1.4.1.10106.3.101291.1.1.19
		htc3000c01v1GenEn OBJECT-TYPE
			SYNTAX BitMask
			MAX-ACCESS read-write
			STATUS current
			DESCRIPTION
				"Generator enable"
		::= { htc3000c01v1Entry 19 }

		-- 1.3.6.1.4.1.10106.3.101291.1.1.21
		htc3000c01v1HDelay OBJECT-TYPE
			SYNTAX DelayPixel5
			MAX-ACCESS read-write
			STATUS current
			DESCRIPTION
				"Allows adjusting the video horizontal delay"
		::= { htc3000c01v1Entry 21 }

		-- 1.3.6.1.4.1.10106.3.101291.1.1.23
		htc3000c01v1VDelay OBJECT-TYPE
			SYNTAX DelayLines2
			MAX-ACCESS read-write
			STATUS current
			DESCRIPTION
				"Allows adjusting the video vertical delay"
		::= { htc3000c01v1Entry 23 }

		-- 1.3.6.1.4.1.10106.3.101291.1.1.25
		htc3000c01v1ModeTc OBJECT-TYPE
			SYNTAX TcModeCombo
			MAX-ACCESS read-write
			STATUS current
			DESCRIPTION
				"It allows selecting Time Code processing mode"
		::= { htc3000c01v1Entry 25 }

		-- 1.3.6.1.4.1.10106.3.101291.1.1.27
		htc3000c01v1SrcTc OBJECT-TYPE
			SYNTAX TcSource
			MAX-ACCESS read-write
			STATUS current
			DESCRIPTION
				"It allows selecting the Time Code source when working on bridge mode"
		::= { htc3000c01v1Entry 27 }

		-- 1.3.6.1.4.1.10106.3.101291.1.1.29
		htc3000c01v1DropFr OBJECT-TYPE
			SYNTAX BitMask
			MAX-ACCESS read-write
			STATUS current
			DESCRIPTION
				"It allows using NTSC time compensated mode"
		::= { htc3000c01v1Entry 29 }

		-- 1.3.6.1.4.1.10106.3.101291.1.1.31
		htc3000c01v1Bgf OBJECT-TYPE
			SYNTAX BgfBits
			MAX-ACCESS read-write
			STATUS current
			DESCRIPTION
				"It allows selecting the Binary Groups Flags to be transmitted in generator mode"
		::= { htc3000c01v1Entry 31 }

		-- 1.3.6.1.4.1.10106.3.101291.1.1.33
		htc3000c01v1EnDlsave OBJECT-TYPE
			SYNTAX BitMask
			MAX-ACCESS read-write
			STATUS current
			DESCRIPTION
				"It allows enabling automatic daylight saving"
		::= { htc3000c01v1Entry 33 }

		-- 1.3.6.1.4.1.10106.3.101291.1.1.35
		htc3000c01v1DateFormat OBJECT-TYPE
			SYNTAX DateFmt
			MAX-ACCESS read-write
			STATUS current
			DESCRIPTION
				"It allows selecting the date format"
		::= { htc3000c01v1Entry 35 }

		-- 1.3.6.1.4.1.10106.3.101291.1.1.37
		htc3000c01v1DvitcIns OBJECT-TYPE
			SYNTAX BitMask
			MAX-ACCESS read-write
			STATUS current
			DESCRIPTION
				"It allows enabling the DVITC insertion at the output video"
		::= { htc3000c01v1Entry 37 }

		-- 1.3.6.1.4.1.10106.3.101291.1.1.39
		htc3000c01v1AtcIns OBJECT-TYPE
			SYNTAX BitMask
			MAX-ACCESS read-write
			STATUS current
			DESCRIPTION
				"It allows enabling the ATC insertion at the output video"
		::= { htc3000c01v1Entry 39 }

		-- 1.3.6.1.4.1.10106.3.101291.1.1.41
		htc3000c01v1AtcType OBJECT-TYPE
			SYNTAX VitcLtc
			MAX-ACCESS read-write
			STATUS current
			DESCRIPTION
				"It allows selecting the ATC packet mode"
		::= { htc3000c01v1Entry 41 }

		-- 1.3.6.1.4.1.10106.3.101291.1.1.43
		htc3000c01v1OsdIns OBJECT-TYPE
			SYNTAX BitMask
			MAX-ACCESS read-write
			STATUS current
			DESCRIPTION
				"It allows enabling the OSD insertion"
		::= { htc3000c01v1Entry 43 }

		-- 1.3.6.1.4.1.10106.3.101291.1.1.45
		htc3000c01v1OsdPosition OBJECT-TYPE
			SYNTAX ClockPosition
			MAX-ACCESS read-write
			STATUS current
			DESCRIPTION
				"It allows selecting the clock position in screen"
		::= { htc3000c01v1Entry 45 }

		-- 1.3.6.1.4.1.10106.3.101291.1.1.47
		htc3000c01v1AuxGen OBJECT-TYPE
			SYNTAX CodeGen
			MAX-ACCESS read-write
			STATUS current
			DESCRIPTION
				"It allows selecting the signal to be transmitted through the analogue audio output"
		::= { htc3000c01v1Entry 47 }

		-- 1.3.6.1.4.1.10106.3.101291.1.1.49
		htc3000c01v1ClockFormat OBJECT-TYPE
			SYNTAX ClockFormat
			MAX-ACCESS read-write
			STATUS current
			DESCRIPTION
				"It allows selectign the clock format"
		::= { htc3000c01v1Entry 49 }

		-- 1.3.6.1.4.1.10106.3.101291.1.1.51
		htc3000c01v1ClockAmPm OBJECT-TYPE
			SYNTAX ClockAmPm
			MAX-ACCESS read-write
			STATUS current
			DESCRIPTION
				"It allows selecting the clock mode"
		::= { htc3000c01v1Entry 51 }

		-- 1.3.6.1.4.1.10106.3.101291.1.1.53
		htc3000c01v1ClockSize OBJECT-TYPE
			SYNTAX ClockSize
			MAX-ACCESS read-write
			STATUS current
			DESCRIPTION
				"It allows selecting the clock size"
		::= { htc3000c01v1Entry 53 }

		-- 1.3.6.1.4.1.10106.3.101291.1.1.55
		htc3000c01v1LevelPips OBJECT-TYPE
			SYNTAX LevelDbfsD
			MAX-ACCESS read-write
			STATUS current
			DESCRIPTION
				"Amplitude of the sound signals generated"
		::= { htc3000c01v1Entry 55 }

		-- 1.3.6.1.4.1.10106.3.101291.1.1.57
		htc3000c01v1MediasGen OBJECT-TYPE
			SYNTAX BitMask
			MAX-ACCESS read-write
			STATUS current
			DESCRIPTION
				"It enables the pips sounding at half past of the generator"
		::= { htc3000c01v1Entry 57 }

		-- 1.3.6.1.4.1.10106.3.101291.1.1.59
		htc3000c01v1FreqPips OBJECT-TYPE
			SYNTAX FrqGen
			MAX-ACCESS read-write
			STATUS current
			DESCRIPTION
				"Frequency of the sound signals generated"
		::= { htc3000c01v1Entry 59 }

		-- 1.3.6.1.4.1.10106.3.101291.1.1.61
		htc3000c01v1NPipsHour OBJECT-TYPE
			SYNTAX Uint4
			MAX-ACCESS read-write
			STATUS current
			DESCRIPTION
				"Number of short pips generated at o'clock"
		::= { htc3000c01v1Entry 61 }

		-- 1.3.6.1.4.1.10106.3.101291.1.1.63
		htc3000c01v1NPipsHalf OBJECT-TYPE
			SYNTAX Uint4
			MAX-ACCESS read-write
			STATUS current
			DESCRIPTION
				"Number of short pips generated at half past"
		::= { htc3000c01v1Entry 63 }

		-- 1.3.6.1.4.1.10106.3.101291.1.1.65
		htc3000c01v1ShortPerHour OBJECT-TYPE
			SYNTAX TimeX100Ms
			MAX-ACCESS read-write
			STATUS current
			DESCRIPTION
				"Length of o'clock short pips"
		::= { htc3000c01v1Entry 65 }

		-- 1.3.6.1.4.1.10106.3.101291.1.1.67
		htc3000c01v1ShortPerHalf OBJECT-TYPE
			SYNTAX TimeX100Ms
			MAX-ACCESS read-write
			STATUS current
			DESCRIPTION
				"Length of half past short pips"
		::= { htc3000c01v1Entry 67 }

		-- 1.3.6.1.4.1.10106.3.101291.1.1.69
		htc3000c01v1LongPerHour OBJECT-TYPE
			SYNTAX TimeX100Ms
			MAX-ACCESS read-write
			STATUS current
			DESCRIPTION
				"Length of o'clock long pip"
		::= { htc3000c01v1Entry 69 }

		-- 1.3.6.1.4.1.10106.3.101291.1.1.71
		htc3000c01v1LongPerHalf OBJECT-TYPE
			SYNTAX TimeX100Ms
			MAX-ACCESS read-write
			STATUS current
			DESCRIPTION
				"Length of half past long pip"
		::= { htc3000c01v1Entry 71 }

		-- 1.3.6.1.4.1.10106.3.101291.1.1.73
		htc3000c01v1SumMonthSt OBJECT-TYPE
			SYNTAX Month
			MAX-ACCESS read-write
			STATUS current
			DESCRIPTION
				"It allows selecting the month when summer time starts"
		::= { htc3000c01v1Entry 73 }

		-- 1.3.6.1.4.1.10106.3.101291.1.1.75
		htc3000c01v1SumWeekSt OBJECT-TYPE
			SYNTAX WeekOfMonth
			MAX-ACCESS read-write
			STATUS current
			DESCRIPTION
				"It allows selecting the week of the month when summer time starts"
		::= { htc3000c01v1Entry 75 }

		-- 1.3.6.1.4.1.10106.3.101291.1.1.77
		htc3000c01v1SumWDaySt OBJECT-TYPE
			SYNTAX Day
			MAX-ACCESS read-write
			STATUS current
			DESCRIPTION
				"It allows selecting the week day when summer time starts"
		::= { htc3000c01v1Entry 77 }

		-- 1.3.6.1.4.1.10106.3.101291.1.1.79
		htc3000c01v1SumHourSt OBJECT-TYPE
			SYNTAX TimeH1
			MAX-ACCESS read-write
			STATUS current
			DESCRIPTION
				"It allows selecting the UTC hour when summer time starts"
		::= { htc3000c01v1Entry 79 }

		-- 1.3.6.1.4.1.10106.3.101291.1.1.81
		htc3000c01v1SumHourOffset OBJECT-TYPE
			SYNTAX Int8
			MAX-ACCESS read-write
			STATUS current
			DESCRIPTION
				"It allows selecting the local time offset at summer time"
		::= { htc3000c01v1Entry 81 }

		-- 1.3.6.1.4.1.10106.3.101291.1.1.83
		htc3000c01v1WinMonthSt OBJECT-TYPE
			SYNTAX Month
			MAX-ACCESS read-write
			STATUS current
			DESCRIPTION
				"It allows selecting the month when winter time starts"
		::= { htc3000c01v1Entry 83 }

		-- 1.3.6.1.4.1.10106.3.101291.1.1.85
		htc3000c01v1WinWeekSt OBJECT-TYPE
			SYNTAX WeekOfMonth
			MAX-ACCESS read-write
			STATUS current
			DESCRIPTION
				"It allows selecting the week of the month when winter time starts"
		::= { htc3000c01v1Entry 85 }

		-- 1.3.6.1.4.1.10106.3.101291.1.1.87
		htc3000c01v1WinWDaySt OBJECT-TYPE
			SYNTAX Day
			MAX-ACCESS read-write
			STATUS current
			DESCRIPTION
				"It allows selecting the week day when winter time starts"
		::= { htc3000c01v1Entry 87 }

		-- 1.3.6.1.4.1.10106.3.101291.1.1.89
		htc3000c01v1WinHourSt OBJECT-TYPE
			SYNTAX TimeH1
			MAX-ACCESS read-write
			STATUS current
			DESCRIPTION
				"It allows selecting the UTC hour when winter time starts"
		::= { htc3000c01v1Entry 89 }

		-- 1.3.6.1.4.1.10106.3.101291.1.1.91
		htc3000c01v1WinHourOffset OBJECT-TYPE
			SYNTAX Int8
			MAX-ACCESS read-write
			STATUS current
			DESCRIPTION
				"It allows selecting the local time offset at winter time"
		::= { htc3000c01v1Entry 91 }

		-- 1.3.6.1.4.1.10106.3.101291.1.1.93
		htc3000c01v1RefAbsent OBJECT-TYPE
			SYNTAX BitFail
			MAX-ACCESS read-only
			STATUS current
			DESCRIPTION
				"There is no reference signal"
		::= { htc3000c01v1Entry 93 }

		-- 1.3.6.1.4.1.10106.3.101291.1.1.94
		htc3000c01v1RefAbsentTrapEnable OBJECT-TYPE
			SYNTAX AlarmEnable
			MAX-ACCESS read-write
			STATUS current
			DESCRIPTION
				"There is no reference signal Trap Enable"
		::= { htc3000c01v1Entry 94 }

		-- 1.3.6.1.4.1.10106.3.101291.1.1.95
		htc3000c01v1RefUnlock OBJECT-TYPE
			SYNTAX BitFail
			MAX-ACCESS read-only
			STATUS current
			DESCRIPTION
				"Reference input unlock fail"
		::= { htc3000c01v1Entry 95 }

		-- 1.3.6.1.4.1.10106.3.101291.1.1.96
		htc3000c01v1RefUnlockTrapEnable OBJECT-TYPE
			SYNTAX AlarmEnable
			MAX-ACCESS read-write
			STATUS current
			DESCRIPTION
				"Reference input unlock fail Trap Enable"
		::= { htc3000c01v1Entry 96 }

		-- 1.3.6.1.4.1.10106.3.101291.1.1.97
		htc3000c01v1NoSignalMain OBJECT-TYPE
			SYNTAX BitFail
			MAX-ACCESS read-only
			STATUS current
			DESCRIPTION
				"There is no SDI signal or the format is not supported in PGM IN"
		::= { htc3000c01v1Entry 97 }

		-- 1.3.6.1.4.1.10106.3.101291.1.1.98
		htc3000c01v1NoSignalMainTrapEnable OBJECT-TYPE
			SYNTAX AlarmEnable
			MAX-ACCESS read-write
			STATUS current
			DESCRIPTION
				"There is no SDI signal or the format is not supported in PGM IN Trap Enable"
		::= { htc3000c01v1Entry 98 }

		-- 1.3.6.1.4.1.10106.3.101291.1.1.99
		htc3000c01v1UnlockMain OBJECT-TYPE
			SYNTAX BitFail
			MAX-ACCESS read-only
			STATUS current
			DESCRIPTION
				"It indicates signal unlock fail"
		::= { htc3000c01v1Entry 99 }

		-- 1.3.6.1.4.1.10106.3.101291.1.1.100
		htc3000c01v1UnlockMainTrapEnable OBJECT-TYPE
			SYNTAX AlarmEnable
			MAX-ACCESS read-write
			STATUS current
			DESCRIPTION
				"It indicates signal unlock fail Trap Enable"
		::= { htc3000c01v1Entry 100 }

		-- 1.3.6.1.4.1.10106.3.101291.1.1.101
		htc3000c01v1EdhErrorMain OBJECT-TYPE
			SYNTAX BitFail
			MAX-ACCESS read-only
			STATUS current
			DESCRIPTION
				"There are EDH/CRC errors on PGM IN"
		::= { htc3000c01v1Entry 101 }

		-- 1.3.6.1.4.1.10106.3.101291.1.1.102
		htc3000c01v1EdhErrorMainTrapEnable OBJECT-TYPE
			SYNTAX AlarmEnable
			MAX-ACCESS read-write
			STATUS current
			DESCRIPTION
				"There are EDH/CRC errors on PGM IN Trap Enable"
		::= { htc3000c01v1Entry 102 }

		-- 1.3.6.1.4.1.10106.3.101291.1.1.103
		htc3000c01v1NoSignalAux OBJECT-TYPE
			SYNTAX BitFail
			MAX-ACCESS read-only
			STATUS current
			DESCRIPTION
				"There is no SDI signal or the format is not supported in AUX IN"
		::= { htc3000c01v1Entry 103 }

		-- 1.3.6.1.4.1.10106.3.101291.1.1.104
		htc3000c01v1NoSignalAuxTrapEnable OBJECT-TYPE
			SYNTAX AlarmEnable
			MAX-ACCESS read-write
			STATUS current
			DESCRIPTION
				"There is no SDI signal or the format is not supported in AUX IN Trap Enable"
		::= { htc3000c01v1Entry 104 }

		-- 1.3.6.1.4.1.10106.3.101291.1.1.105
		htc3000c01v1UnlockAux OBJECT-TYPE
			SYNTAX BitFail
			MAX-ACCESS read-only
			STATUS current
			DESCRIPTION
				"It indicates signal AUX IN unlock fail"
		::= { htc3000c01v1Entry 105 }

		-- 1.3.6.1.4.1.10106.3.101291.1.1.106
		htc3000c01v1UnlockAuxTrapEnable OBJECT-TYPE
			SYNTAX AlarmEnable
			MAX-ACCESS read-write
			STATUS current
			DESCRIPTION
				"It indicates signal AUX IN unlock fail Trap Enable"
		::= { htc3000c01v1Entry 106 }

		-- 1.3.6.1.4.1.10106.3.101291.1.1.107
		htc3000c01v1EdhErrorAux OBJECT-TYPE
			SYNTAX BitFail
			MAX-ACCESS read-only
			STATUS current
			DESCRIPTION
				"There are EDH/CRC errors on AUX IN signal"
		::= { htc3000c01v1Entry 107 }

		-- 1.3.6.1.4.1.10106.3.101291.1.1.108
		htc3000c01v1EdhErrorAuxTrapEnable OBJECT-TYPE
			SYNTAX AlarmEnable
			MAX-ACCESS read-write
			STATUS current
			DESCRIPTION
				"There are EDH/CRC errors on AUX IN signal Trap Enable"
		::= { htc3000c01v1Entry 108 }

		-- 1.3.6.1.4.1.10106.3.101291.1.1.109
		htc3000c01v1IncompFmt OBJECT-TYPE
			SYNTAX BitFail
			MAX-ACCESS read-only
			STATUS current
			DESCRIPTION
				"It indicates if there are incompatible formats (european-american)"
		::= { htc3000c01v1Entry 109 }

		-- 1.3.6.1.4.1.10106.3.101291.1.1.110
		htc3000c01v1IncompFmtTrapEnable OBJECT-TYPE
			SYNTAX AlarmEnable
			MAX-ACCESS read-write
			STATUS current
			DESCRIPTION
				"It indicates if there are incompatible formats (european-american) Trap Enable"
		::= { htc3000c01v1Entry 110 }

		-- 1.3.6.1.4.1.10106.3.101291.1.1.111
		htc3000c01v1TcFail OBJECT-TYPE
			SYNTAX BitFail
			MAX-ACCESS read-only
			STATUS current
			DESCRIPTION
				"It indicates if there is a reception Time Code fail"
		::= { htc3000c01v1Entry 111 }

		-- 1.3.6.1.4.1.10106.3.101291.1.1.112
		htc3000c01v1TcFailTrapEnable OBJECT-TYPE
			SYNTAX AlarmEnable
			MAX-ACCESS read-write
			STATUS current
			DESCRIPTION
				"It indicates if there is a reception Time Code fail Trap Enable"
		::= { htc3000c01v1Entry 112 }

		-- 1.3.6.1.4.1.10106.3.101291.1.1.113
		htc3000c01v1FormatRef OBJECT-TYPE
			SYNTAX SdiHd3gFmt7
			MAX-ACCESS read-only
			STATUS current
			DESCRIPTION
				"It indicates the input reference signal format"
		::= { htc3000c01v1Entry 113 }

		-- 1.3.6.1.4.1.10106.3.101291.1.1.115
		htc3000c01v1FormatMainIn OBJECT-TYPE
			SYNTAX SdiHd3gFmt7
			MAX-ACCESS read-only
			STATUS current
			DESCRIPTION
				"It indicates the SDI PGM IN received signal format"
		::= { htc3000c01v1Entry 115 }

		-- 1.3.6.1.4.1.10106.3.101291.1.1.117
		htc3000c01v1FormatAuxIn OBJECT-TYPE
			SYNTAX SdiHd3gFmt7
			MAX-ACCESS read-only
			STATUS current
			DESCRIPTION
				"It indicates the SDI AUX IN received signal format"
		::= { htc3000c01v1Entry 117 }

		-- 1.3.6.1.4.1.10106.3.101291.1.1.119
		htc3000c01v1FormatMainTx OBJECT-TYPE
			SYNTAX SdiHd3gFmt7
			MAX-ACCESS read-only
			STATUS current
			DESCRIPTION
				"It indicates the SDI OUT transmited signal format"
		::= { htc3000c01v1Entry 119 }

		-- 1.3.6.1.4.1.10106.3.101291.1.1.121
		htc3000c01v1SigDelay OBJECT-TYPE
			SYNTAX DelayX20Us
			MAX-ACCESS read-only
			STATUS current
			DESCRIPTION
				"It indicates the input to output delay"
		::= { htc3000c01v1Entry 121 }

		-- 1.3.6.1.4.1.10106.3.101291.1.1.123
		htc3000c01v1DvitcPres OBJECT-TYPE
			SYNTAX BitFailN
			MAX-ACCESS read-only
			STATUS current
			DESCRIPTION
				"It indicates the DVITC presence at the auxiliar input video"
		::= { htc3000c01v1Entry 123 }

		-- 1.3.6.1.4.1.10106.3.101291.1.1.125
		htc3000c01v1AtcVitcPres OBJECT-TYPE
			SYNTAX BitFailN
			MAX-ACCESS read-only
			STATUS current
			DESCRIPTION
				"It indicates the ATC/VITC presence at the auxiliar input video"
		::= { htc3000c01v1Entry 125 }

		-- 1.3.6.1.4.1.10106.3.101291.1.1.127
		htc3000c01v1AtcLtcPres OBJECT-TYPE
			SYNTAX BitFailN
			MAX-ACCESS read-only
			STATUS current
			DESCRIPTION
				"It inidcates the ATC/LTC presence at the auxiliar input video"
		::= { htc3000c01v1Entry 127 }

		-- 1.3.6.1.4.1.10106.3.101291.1.1.129
		htc3000c01v1LtcPres OBJECT-TYPE
			SYNTAX BitFailN
			MAX-ACCESS read-only
			STATUS current
			DESCRIPTION
				"It indicates the LTC presence"
		::= { htc3000c01v1Entry 129 }

		-- 1.3.6.1.4.1.10106.3.101291.1.1.131
		htc3000c01v1BgfSt OBJECT-TYPE
			SYNTAX BgfBits
			MAX-ACCESS read-only
			STATUS current
			DESCRIPTION
				"Binary group flags"
		::= { htc3000c01v1Entry 131 }

		-- 1.3.6.1.4.1.10106.3.101291.1.1.133
		htc3000c01v1DropFSt OBJECT-TYPE
			SYNTAX Bit0No1Yes
			MAX-ACCESS read-only
			STATUS current
			DESCRIPTION
				"Drop frame flag"
		::= { htc3000c01v1Entry 133 }

		-- 1.3.6.1.4.1.10106.3.101291.1.1.135
		htc3000c01v1ColorFSt OBJECT-TYPE
			SYNTAX Bit0No1Yes
			MAX-ACCESS read-only
			STATUS current
			DESCRIPTION
				"Color flag"
		::= { htc3000c01v1Entry 135 }

		-- 1.3.6.1.4.1.10106.3.101291.1.1.137
		htc3000c01v1SerialNo OBJECT-TYPE
			SYNTAX SerialNo
			MAX-ACCESS read-only
			STATUS current
			DESCRIPTION
				"Serial number"
		::= { htc3000c01v1Entry 137 }

		-- 1.3.6.1.4.1.10106.3.101291.1.1.139
		htc3000c01v1DateFmtRx OBJECT-TYPE
			SYNTAX DateFmt
			MAX-ACCESS read-write
			STATUS current
			DESCRIPTION
				"It allows selecting the date format within the received Time Code"
		::= { htc3000c01v1Entry 139 }

		-- 1.3.6.1.4.1.10106.3.101291.1.1.141
		htc3000c01v1EnDateGen OBJECT-TYPE
			SYNTAX BitMask
			MAX-ACCESS read-write
			STATUS current
			DESCRIPTION
				"It allows enabling the date insertion in TC when working in generator mode"
		::= { htc3000c01v1Entry 141 }

		-- 1.3.6.1.4.1.10106.3.473501
		tle3001c02v1 OBJECT IDENTIFIER ::= { albalaProducts 473501 }

		-- 1.3.6.1.4.1.10106.3.473501.1
		tle3001c02v1Table  OBJECT-TYPE
			SYNTAX SEQUENCE OF Tle3001c02v1Entry
			MAX-ACCESS not-accessible
			STATUS current
			DESCRIPTION
				"Module  TLE3001C02V1 Table"
			::= { tle3001c02v1 1 }

		-- 1.3.6.1.4.1.10106.3.473501.1.1
		tle3001c02v1Entry  OBJECT-TYPE
			SYNTAX Tle3001c02v1Entry
			MAX-ACCESS not-accessible
			STATUS current
			DESCRIPTION
				"Module TLE3001C02V1 Entry"
			INDEX { tle3001c02v1Index }
			::= { tle3001c02v1Table 1 }

			Tle3001c02v1Entry ::=
			SEQUENCE {
				tle3001c02v1Index
				ModuleIndex,
				tle3001c02v1Serial485232
				Bit04851232,
				tle3001c02v1ConsoleEna
				Bit0No1Yes,
				tle3001c02v1Gpo1
				Bit0Ina1Act,
				tle3001c02v1Gpo2
				Bit0Ina1Act,
				tle3001c02v1Gpo3
				Bit0Ina1Act,
				tle3001c02v1Gpo4
				Bit0Ina1Act,
				tle3001c02v1InvertGpi1Pol
				Bit0No1Yes,
				tle3001c02v1InvertGpi2Pol
				Bit0No1Yes,
				tle3001c02v1InvertGpi3Pol
				Bit0No1Yes,
				tle3001c02v1InvertGpi4Pol
				Bit0No1Yes,
				tle3001c02v1InvertGpo1Pol
				Bit0No1Yes,
				tle3001c02v1InvertGpo2Pol
				Bit0No1Yes,
				tle3001c02v1InvertGpo3Pol
				Bit0No1Yes,
				tle3001c02v1InvertGpo4Pol
				Bit0No1Yes,
				tle3001c02v1Gpi1
				Bit0Ina1Act,
				tle3001c02v1Gpi1TrapEnable
				AlarmEnable,
				tle3001c02v1Gpi2
				Bit0Ina1Act,
				tle3001c02v1Gpi2TrapEnable
				AlarmEnable,
				tle3001c02v1Gpi3
				Bit0Ina1Act,
				tle3001c02v1Gpi3TrapEnable
				AlarmEnable,
				tle3001c02v1Gpi4
				Bit0Ina1Act,
				tle3001c02v1Gpi4TrapEnable
				AlarmEnable,
				tle3001c02v1RedBoard
				Bit0No1Yes,
				tle3001c02v1RedBoardTrapEnable
				AlarmEnable,
				tle3001c02v1EthLink
				Bit0No1Yes,
				tle3001c02v1EthLinkTrapEnable
				AlarmEnable,
				tle3001c02v1EthRedAct
				Bit0No1Yes,
				tle3001c02v1EthRedActTrapEnable
				AlarmEnable,
				tle3001c02v1SerialNo
				SerialNo
			 }

		-- 1.3.6.1.4.1.10106.3.101291.1.1.1
		tle3001c02v1Index OBJECT-TYPE
			SYNTAX ModuleIndex
			MAX-ACCESS read-only
			STATUS current
			DESCRIPTION
				"Index of TLE3001C02V1 Table"
		::= { tle3001c02v1Entry 1 }

		-- 1.3.6.1.4.1.10106.3.101291.1.1.3
		tle3001c02v1Serial485232 OBJECT-TYPE
			SYNTAX Bit04851232
			MAX-ACCESS read-write
			STATUS current
			DESCRIPTION
				"Allows selecting the serial port levels"
		::= { tle3001c02v1Entry 3 }

		-- 1.3.6.1.4.1.10106.3.101291.1.1.5
		tle3001c02v1ConsoleEna OBJECT-TYPE
			SYNTAX Bit0No1Yes
			MAX-ACCESS read-write
			STATUS current
			DESCRIPTION
				"Allows using the serial port for the consola"
		::= { tle3001c02v1Entry 5 }

		-- 1.3.6.1.4.1.10106.3.101291.1.1.7
		tle3001c02v1Gpo1 OBJECT-TYPE
			SYNTAX Bit0Ina1Act
			MAX-ACCESS read-write
			STATUS current
			DESCRIPTION
				"Allows control of GPO1"
		::= { tle3001c02v1Entry 7 }

		-- 1.3.6.1.4.1.10106.3.101291.1.1.9
		tle3001c02v1Gpo2 OBJECT-TYPE
			SYNTAX Bit0Ina1Act
			MAX-ACCESS read-write
			STATUS current
			DESCRIPTION
				"Allows control of GPO2"
		::= { tle3001c02v1Entry 9 }

		-- 1.3.6.1.4.1.10106.3.101291.1.1.11
		tle3001c02v1Gpo3 OBJECT-TYPE
			SYNTAX Bit0Ina1Act
			MAX-ACCESS read-write
			STATUS current
			DESCRIPTION
				"Allows control of GPO3"
		::= { tle3001c02v1Entry 11 }

		-- 1.3.6.1.4.1.10106.3.101291.1.1.13
		tle3001c02v1Gpo4 OBJECT-TYPE
			SYNTAX Bit0Ina1Act
			MAX-ACCESS read-write
			STATUS current
			DESCRIPTION
				"Allows control of GPO4"
		::= { tle3001c02v1Entry 13 }

		-- 1.3.6.1.4.1.10106.3.101291.1.1.15
		tle3001c02v1InvertGpi1Pol OBJECT-TYPE
			SYNTAX Bit0No1Yes
			MAX-ACCESS read-write
			STATUS current
			DESCRIPTION
				"Changes GPI1 polarity to normally closed"
		::= { tle3001c02v1Entry 15 }

		-- 1.3.6.1.4.1.10106.3.101291.1.1.17
		tle3001c02v1InvertGpi2Pol OBJECT-TYPE
			SYNTAX Bit0No1Yes
			MAX-ACCESS read-write
			STATUS current
			DESCRIPTION
				"Changes GPI2 polarity to normally closed"
		::= { tle3001c02v1Entry 17 }

		-- 1.3.6.1.4.1.10106.3.101291.1.1.19
		tle3001c02v1InvertGpi3Pol OBJECT-TYPE
			SYNTAX Bit0No1Yes
			MAX-ACCESS read-write
			STATUS current
			DESCRIPTION
				"Changes GPI3 polarity to normally closed"
		::= { tle3001c02v1Entry 19 }

		-- 1.3.6.1.4.1.10106.3.101291.1.1.21
		tle3001c02v1InvertGpi4Pol OBJECT-TYPE
			SYNTAX Bit0No1Yes
			MAX-ACCESS read-write
			STATUS current
			DESCRIPTION
				"Changes GPI4 polarity to normally closed"
		::= { tle3001c02v1Entry 21 }

		-- 1.3.6.1.4.1.10106.3.101291.1.1.23
		tle3001c02v1InvertGpo1Pol OBJECT-TYPE
			SYNTAX Bit0No1Yes
			MAX-ACCESS read-write
			STATUS current
			DESCRIPTION
				"Allows inverting GPO1 polarity"
		::= { tle3001c02v1Entry 23 }

		-- 1.3.6.1.4.1.10106.3.101291.1.1.25
		tle3001c02v1InvertGpo2Pol OBJECT-TYPE
			SYNTAX Bit0No1Yes
			MAX-ACCESS read-write
			STATUS current
			DESCRIPTION
				"Allows inverting GPO2 polarity"
		::= { tle3001c02v1Entry 25 }

		-- 1.3.6.1.4.1.10106.3.101291.1.1.27
		tle3001c02v1InvertGpo3Pol OBJECT-TYPE
			SYNTAX Bit0No1Yes
			MAX-ACCESS read-write
			STATUS current
			DESCRIPTION
				"Allows inverting GPO3 polarity"
		::= { tle3001c02v1Entry 27 }

		-- 1.3.6.1.4.1.10106.3.101291.1.1.29
		tle3001c02v1InvertGpo4Pol OBJECT-TYPE
			SYNTAX Bit0No1Yes
			MAX-ACCESS read-write
			STATUS current
			DESCRIPTION
				"Allows inverting GPO4 polarity"
		::= { tle3001c02v1Entry 29 }

		-- 1.3.6.1.4.1.10106.3.101291.1.1.31
		tle3001c02v1Gpi1 OBJECT-TYPE
			SYNTAX Bit0Ina1Act
			MAX-ACCESS read-only
			STATUS current
			DESCRIPTION
				"GPI1 status"
		::= { tle3001c02v1Entry 31 }

		-- 1.3.6.1.4.1.10106.3.101291.1.1.32
		tle3001c02v1Gpi1TrapEnable OBJECT-TYPE
			SYNTAX AlarmEnable
			MAX-ACCESS read-write
			STATUS current
			DESCRIPTION
				"GPI1 status Trap Enable"
		::= { tle3001c02v1Entry 32 }

		-- 1.3.6.1.4.1.10106.3.101291.1.1.33
		tle3001c02v1Gpi2 OBJECT-TYPE
			SYNTAX Bit0Ina1Act
			MAX-ACCESS read-only
			STATUS current
			DESCRIPTION
				"GPI2 status"
		::= { tle3001c02v1Entry 33 }

		-- 1.3.6.1.4.1.10106.3.101291.1.1.34
		tle3001c02v1Gpi2TrapEnable OBJECT-TYPE
			SYNTAX AlarmEnable
			MAX-ACCESS read-write
			STATUS current
			DESCRIPTION
				"GPI2 status Trap Enable"
		::= { tle3001c02v1Entry 34 }

		-- 1.3.6.1.4.1.10106.3.101291.1.1.35
		tle3001c02v1Gpi3 OBJECT-TYPE
			SYNTAX Bit0Ina1Act
			MAX-ACCESS read-only
			STATUS current
			DESCRIPTION
				"GPI3 status"
		::= { tle3001c02v1Entry 35 }

		-- 1.3.6.1.4.1.10106.3.101291.1.1.36
		tle3001c02v1Gpi3TrapEnable OBJECT-TYPE
			SYNTAX AlarmEnable
			MAX-ACCESS read-write
			STATUS current
			DESCRIPTION
				"GPI3 status Trap Enable"
		::= { tle3001c02v1Entry 36 }

		-- 1.3.6.1.4.1.10106.3.101291.1.1.37
		tle3001c02v1Gpi4 OBJECT-TYPE
			SYNTAX Bit0Ina1Act
			MAX-ACCESS read-only
			STATUS current
			DESCRIPTION
				"GPI4 status"
		::= { tle3001c02v1Entry 37 }

		-- 1.3.6.1.4.1.10106.3.101291.1.1.38
		tle3001c02v1Gpi4TrapEnable OBJECT-TYPE
			SYNTAX AlarmEnable
			MAX-ACCESS read-write
			STATUS current
			DESCRIPTION
				"GPI4 status Trap Enable"
		::= { tle3001c02v1Entry 38 }

		-- 1.3.6.1.4.1.10106.3.101291.1.1.39
		tle3001c02v1RedBoard OBJECT-TYPE
			SYNTAX Bit0No1Yes
			MAX-ACCESS read-only
			STATUS current
			DESCRIPTION
				"Indicates that there are two modules in redundant configuration"
		::= { tle3001c02v1Entry 39 }

		-- 1.3.6.1.4.1.10106.3.101291.1.1.40
		tle3001c02v1RedBoardTrapEnable OBJECT-TYPE
			SYNTAX AlarmEnable
			MAX-ACCESS read-write
			STATUS current
			DESCRIPTION
				"Indicates that there are two modules in redundant configuration Trap Enable"
		::= { tle3001c02v1Entry 40 }

		-- 1.3.6.1.4.1.10106.3.101291.1.1.41
		tle3001c02v1EthLink OBJECT-TYPE
			SYNTAX Bit0No1Yes
			MAX-ACCESS read-only
			STATUS current
			DESCRIPTION
				"Indicates that the Ethernet link is OK"
		::= { tle3001c02v1Entry 41 }

		-- 1.3.6.1.4.1.10106.3.101291.1.1.42
		tle3001c02v1EthLinkTrapEnable OBJECT-TYPE
			SYNTAX AlarmEnable
			MAX-ACCESS read-write
			STATUS current
			DESCRIPTION
				"Indicates that the Ethernet link is OK Trap Enable"
		::= { tle3001c02v1Entry 42 }

		-- 1.3.6.1.4.1.10106.3.101291.1.1.43
		tle3001c02v1EthRedAct OBJECT-TYPE
			SYNTAX Bit0No1Yes
			MAX-ACCESS read-only
			STATUS current
			DESCRIPTION
				"Indicates that this is the active module of the redundant configuration"
		::= { tle3001c02v1Entry 43 }

		-- 1.3.6.1.4.1.10106.3.101291.1.1.44
		tle3001c02v1EthRedActTrapEnable OBJECT-TYPE
			SYNTAX AlarmEnable
			MAX-ACCESS read-write
			STATUS current
			DESCRIPTION
				"Indicates that this is the active module of the redundant configuration Trap Enable"
		::= { tle3001c02v1Entry 44 }

		-- 1.3.6.1.4.1.10106.3.101291.1.1.45
		tle3001c02v1SerialNo OBJECT-TYPE
			SYNTAX SerialNo
			MAX-ACCESS read-only
			STATUS current
			DESCRIPTION
				"Serial number"
		::= { tle3001c02v1Entry 45 }

		-- 1.3.6.1.4.1.10106.3.474701
		adf2008c01v1 OBJECT IDENTIFIER ::= { albalaProducts 474701 }

		-- 1.3.6.1.4.1.10106.3.474701.1
		adf2008c01v1Table  OBJECT-TYPE
			SYNTAX SEQUENCE OF Adf2008c01v1Entry
			MAX-ACCESS not-accessible
			STATUS current
			DESCRIPTION
				"Module  ADF2008C01V1 Table"
			::= { adf2008c01v1 1 }

		-- 1.3.6.1.4.1.10106.3.474701.1.1
		adf2008c01v1Entry  OBJECT-TYPE
			SYNTAX Adf2008c01v1Entry
			MAX-ACCESS not-accessible
			STATUS current
			DESCRIPTION
				"Module ADF2008C01V1 Entry"
			INDEX { adf2008c01v1Index }
			::= { adf2008c01v1Table 1 }

			Adf2008c01v1Entry ::=
			SEQUENCE {
				adf2008c01v1Index
				ModuleIndex,
				adf2008c01v1ActivePreset
				Preset16Active,
				adf2008c01v1LoadPreset
				Preset16Load,
				adf2008c01v1SavePreset
				Preset16Save,
				adf2008c01v1R2lOut1Src
				Hde2R2lSrcA,
				adf2008c01v1R2lOut2Src
				Hde2R2lSrcA,
				adf2008c01v1R2lOut3Src
				Hde2R2lSrcA,
				adf2008c01v1R2lOut4Src
				Hde2R2lSrcA,
				adf2008c01v1R2lOut5Src
				Hde2R2lSrcA,
				adf2008c01v1R2lOut6Src
				Hde2R2lSrcA,
				adf2008c01v1R2lOut7Src
				Hde2R2lSrcA,
				adf2008c01v1R2lOut8Src
				Hde2R2lSrcA,
				adf2008c01v1R2lOut9Src
				Hde2R2lSrcA,
				adf2008c01v1R2lOut10Src
				Hde2R2lSrcA,
				adf2008c01v1R2lOut11Src
				Hde2R2lSrcA,
				adf2008c01v1R2lOut12Src
				Hde2R2lSrcA,
				adf2008c01v1R2lOut13Src
				Hde2R2lSrcA,
				adf2008c01v1R2lOut14Src
				Hde2R2lSrcA,
				adf2008c01v1R2lOut15Src
				Hde2R2lSrcA,
				adf2008c01v1R2lOut16Src
				Hde2R2lSrcA,
				adf2008c01v1L2rOut1Src
				Hde2L2rSrcA,
				adf2008c01v1L2rOut2Src
				Hde2L2rSrcA,
				adf2008c01v1L2rOut3Src
				Hde2L2rSrcA,
				adf2008c01v1L2rOut4Src
				Hde2L2rSrcA,
				adf2008c01v1L2rOut5Src
				Hde2L2rSrcA,
				adf2008c01v1L2rOut6Src
				Hde2L2rSrcA,
				adf2008c01v1L2rOut7Src
				Hde2L2rSrcA,
				adf2008c01v1L2rOut8Src
				Hde2L2rSrcA,
				adf2008c01v1L2rOut9Src
				Hde2L2rSrcA,
				adf2008c01v1L2rOut10Src
				Hde2L2rSrcA,
				adf2008c01v1L2rOut11Src
				Hde2L2rSrcA,
				adf2008c01v1L2rOut12Src
				Hde2L2rSrcA,
				adf2008c01v1L2rOut13Src
				Hde2L2rSrcA,
				adf2008c01v1L2rOut14Src
				Hde2L2rSrcA,
				adf2008c01v1L2rOut15Src
				Hde2L2rSrcA,
				adf2008c01v1L2rOut16Src
				Hde2L2rSrcA,
				adf2008c01v1GainIn1
				Gain24dbMute,
				adf2008c01v1GainIn2
				Gain24dbMute,
				adf2008c01v1GainIn3
				Gain24dbMute,
				adf2008c01v1GainIn4
				Gain24dbMute,
				adf2008c01v1GainIn5
				Gain24dbMute,
				adf2008c01v1GainIn6
				Gain24dbMute,
				adf2008c01v1GainIn7
				Gain24dbMute,
				adf2008c01v1GainIn8
				Gain24dbMute,
				adf2008c01v1AnalogIn1Level
				LevelDbfsA,
				adf2008c01v1AnalogIn2Level
				LevelDbfsA,
				adf2008c01v1AnalogIn3Level
				LevelDbfsA,
				adf2008c01v1AnalogIn4Level
				LevelDbfsA,
				adf2008c01v1AnalogIn5Level
				LevelDbfsA,
				adf2008c01v1AnalogIn6Level
				LevelDbfsA,
				adf2008c01v1AnalogIn7Level
				LevelDbfsA,
				adf2008c01v1AnalogIn8Level
				LevelDbfsA,
				adf2008c01v1BackplaneLocked
				BitFailN,
				adf2008c01v1BackplaneLockedTrapEnable
				AlarmEnable,
				adf2008c01v1L2rIn1Pres
				BitFailN,
				adf2008c01v1L2rIn2Pres
				BitFailN,
				adf2008c01v1L2rIn3Pres
				BitFailN,
				adf2008c01v1L2rIn4Pres
				BitFailN,
				adf2008c01v1L2rIn5Pres
				BitFailN,
				adf2008c01v1L2rIn6Pres
				BitFailN,
				adf2008c01v1L2rIn7Pres
				BitFailN,
				adf2008c01v1L2rIn8Pres
				BitFailN,
				adf2008c01v1L2rIn9Pres
				BitFailN,
				adf2008c01v1L2rIn10Pres
				BitFailN,
				adf2008c01v1L2rIn11Pres
				BitFailN,
				adf2008c01v1L2rIn12Pres
				BitFailN,
				adf2008c01v1L2rIn13Pres
				BitFailN,
				adf2008c01v1L2rIn14Pres
				BitFailN,
				adf2008c01v1L2rIn15Pres
				BitFailN,
				adf2008c01v1L2rIn16Pres
				BitFailN,
				adf2008c01v1R2lIn1Pres
				BitFailN,
				adf2008c01v1R2lIn2Pres
				BitFailN,
				adf2008c01v1R2lIn3Pres
				BitFailN,
				adf2008c01v1R2lIn4Pres
				BitFailN,
				adf2008c01v1R2lIn5Pres
				BitFailN,
				adf2008c01v1R2lIn6Pres
				BitFailN,
				adf2008c01v1R2lIn7Pres
				BitFailN,
				adf2008c01v1R2lIn8Pres
				BitFailN,
				adf2008c01v1R2lIn9Pres
				BitFailN,
				adf2008c01v1R2lIn10Pres
				BitFailN,
				adf2008c01v1R2lIn11Pres
				BitFailN,
				adf2008c01v1R2lIn12Pres
				BitFailN,
				adf2008c01v1R2lIn13Pres
				BitFailN,
				adf2008c01v1R2lIn14Pres
				BitFailN,
				adf2008c01v1R2lIn15Pres
				BitFailN,
				adf2008c01v1R2lIn16Pres
				BitFailN,
				adf2008c01v1AnalogInOverfl
				BitFail,
				adf2008c01v1AnalogInOverflTrapEnable
				AlarmEnable,
				adf2008c01v1SerialNo
				SerialNo,
				adf2008c01v1OverloadAlarm1
				BitFail,
				adf2008c01v1OverloadAlarm2
				BitFail,
				adf2008c01v1OverloadAlarm3
				BitFail,
				adf2008c01v1OverloadAlarm4
				BitFail,
				adf2008c01v1OverloadAlarm5
				BitFail,
				adf2008c01v1OverloadAlarm6
				BitFail,
				adf2008c01v1OverloadAlarm7
				BitFail,
				adf2008c01v1OverloadAlarm8
				BitFail
			 }

		-- 1.3.6.1.4.1.10106.3.101291.1.1.1
		adf2008c01v1Index OBJECT-TYPE
			SYNTAX ModuleIndex
			MAX-ACCESS read-only
			STATUS current
			DESCRIPTION
				"Index of ADF2008C01V1 Table"
		::= { adf2008c01v1Entry 1 }

		-- 1.3.6.1.4.1.10106.3.101291.1.1.3
		adf2008c01v1ActivePreset OBJECT-TYPE
			SYNTAX Preset16Active
			MAX-ACCESS read-only
			STATUS current
			DESCRIPTION
				"Shows the active preset"
		::= { adf2008c01v1Entry 3 }

		-- 1.3.6.1.4.1.10106.3.101291.1.1.5
		adf2008c01v1LoadPreset OBJECT-TYPE
			SYNTAX Preset16Load
			MAX-ACCESS read-write
			STATUS current
			DESCRIPTION
				"Allows loading a preset"
		::= { adf2008c01v1Entry 5 }

		-- 1.3.6.1.4.1.10106.3.101291.1.1.7
		adf2008c01v1SavePreset OBJECT-TYPE
			SYNTAX Preset16Save
			MAX-ACCESS read-write
			STATUS current
			DESCRIPTION
				"Allows saving a preset"
		::= { adf2008c01v1Entry 7 }

		-- 1.3.6.1.4.1.10106.3.101291.1.1.9
		adf2008c01v1R2lOut1Src OBJECT-TYPE
			SYNTAX Hde2R2lSrcA
			MAX-ACCESS read-write
			STATUS current
			DESCRIPTION
				"Insertion source used in R2L OUT channel 1"
		::= { adf2008c01v1Entry 9 }

		-- 1.3.6.1.4.1.10106.3.101291.1.1.11
		adf2008c01v1R2lOut2Src OBJECT-TYPE
			SYNTAX Hde2R2lSrcA
			MAX-ACCESS read-write
			STATUS current
			DESCRIPTION
				"Insertion source used in R2L OUT channel 2"
		::= { adf2008c01v1Entry 11 }

		-- 1.3.6.1.4.1.10106.3.101291.1.1.13
		adf2008c01v1R2lOut3Src OBJECT-TYPE
			SYNTAX Hde2R2lSrcA
			MAX-ACCESS read-write
			STATUS current
			DESCRIPTION
				"Insertion source used in R2L OUT channel 3"
		::= { adf2008c01v1Entry 13 }

		-- 1.3.6.1.4.1.10106.3.101291.1.1.15
		adf2008c01v1R2lOut4Src OBJECT-TYPE
			SYNTAX Hde2R2lSrcA
			MAX-ACCESS read-write
			STATUS current
			DESCRIPTION
				"Insertion source used in R2L OUT channel 4"
		::= { adf2008c01v1Entry 15 }

		-- 1.3.6.1.4.1.10106.3.101291.1.1.17
		adf2008c01v1R2lOut5Src OBJECT-TYPE
			SYNTAX Hde2R2lSrcA
			MAX-ACCESS read-write
			STATUS current
			DESCRIPTION
				"Insertion source used in R2L OUT channel 5"
		::= { adf2008c01v1Entry 17 }

		-- 1.3.6.1.4.1.10106.3.101291.1.1.19
		adf2008c01v1R2lOut6Src OBJECT-TYPE
			SYNTAX Hde2R2lSrcA
			MAX-ACCESS read-write
			STATUS current
			DESCRIPTION
				"Insertion source used in R2L OUT channel 6"
		::= { adf2008c01v1Entry 19 }

		-- 1.3.6.1.4.1.10106.3.101291.1.1.21
		adf2008c01v1R2lOut7Src OBJECT-TYPE
			SYNTAX Hde2R2lSrcA
			MAX-ACCESS read-write
			STATUS current
			DESCRIPTION
				"Insertion source used in R2L OUT channel 7"
		::= { adf2008c01v1Entry 21 }

		-- 1.3.6.1.4.1.10106.3.101291.1.1.23
		adf2008c01v1R2lOut8Src OBJECT-TYPE
			SYNTAX Hde2R2lSrcA
			MAX-ACCESS read-write
			STATUS current
			DESCRIPTION
				"Insertion source used in R2L OUT channel 8"
		::= { adf2008c01v1Entry 23 }

		-- 1.3.6.1.4.1.10106.3.101291.1.1.25
		adf2008c01v1R2lOut9Src OBJECT-TYPE
			SYNTAX Hde2R2lSrcA
			MAX-ACCESS read-write
			STATUS current
			DESCRIPTION
				"Insertion source used in R2L OUT channel 9"
		::= { adf2008c01v1Entry 25 }

		-- 1.3.6.1.4.1.10106.3.101291.1.1.27
		adf2008c01v1R2lOut10Src OBJECT-TYPE
			SYNTAX Hde2R2lSrcA
			MAX-ACCESS read-write
			STATUS current
			DESCRIPTION
				"Insertion source used in R2L OUT channel 10"
		::= { adf2008c01v1Entry 27 }

		-- 1.3.6.1.4.1.10106.3.101291.1.1.29
		adf2008c01v1R2lOut11Src OBJECT-TYPE
			SYNTAX Hde2R2lSrcA
			MAX-ACCESS read-write
			STATUS current
			DESCRIPTION
				"Insertion source used in R2L OUT channel 11"
		::= { adf2008c01v1Entry 29 }

		-- 1.3.6.1.4.1.10106.3.101291.1.1.31
		adf2008c01v1R2lOut12Src OBJECT-TYPE
			SYNTAX Hde2R2lSrcA
			MAX-ACCESS read-write
			STATUS current
			DESCRIPTION
				"Insertion source used in R2L OUT channel 12"
		::= { adf2008c01v1Entry 31 }

		-- 1.3.6.1.4.1.10106.3.101291.1.1.33
		adf2008c01v1R2lOut13Src OBJECT-TYPE
			SYNTAX Hde2R2lSrcA
			MAX-ACCESS read-write
			STATUS current
			DESCRIPTION
				"Insertion source used in R2L OUT channel 13"
		::= { adf2008c01v1Entry 33 }

		-- 1.3.6.1.4.1.10106.3.101291.1.1.35
		adf2008c01v1R2lOut14Src OBJECT-TYPE
			SYNTAX Hde2R2lSrcA
			MAX-ACCESS read-write
			STATUS current
			DESCRIPTION
				"Insertion source used in R2L OUT channel 14"
		::= { adf2008c01v1Entry 35 }

		-- 1.3.6.1.4.1.10106.3.101291.1.1.37
		adf2008c01v1R2lOut15Src OBJECT-TYPE
			SYNTAX Hde2R2lSrcA
			MAX-ACCESS read-write
			STATUS current
			DESCRIPTION
				"Insertion source used in R2L OUT channel 15"
		::= { adf2008c01v1Entry 37 }

		-- 1.3.6.1.4.1.10106.3.101291.1.1.39
		adf2008c01v1R2lOut16Src OBJECT-TYPE
			SYNTAX Hde2R2lSrcA
			MAX-ACCESS read-write
			STATUS current
			DESCRIPTION
				"Insertion source used in R2L OUT channel 16"
		::= { adf2008c01v1Entry 39 }

		-- 1.3.6.1.4.1.10106.3.101291.1.1.41
		adf2008c01v1L2rOut1Src OBJECT-TYPE
			SYNTAX Hde2L2rSrcA
			MAX-ACCESS read-write
			STATUS current
			DESCRIPTION
				"Insertion source used in L2R OUT channel 1"
		::= { adf2008c01v1Entry 41 }

		-- 1.3.6.1.4.1.10106.3.101291.1.1.43
		adf2008c01v1L2rOut2Src OBJECT-TYPE
			SYNTAX Hde2L2rSrcA
			MAX-ACCESS read-write
			STATUS current
			DESCRIPTION
				"Insertion source used in L2R OUT channel 2"
		::= { adf2008c01v1Entry 43 }

		-- 1.3.6.1.4.1.10106.3.101291.1.1.45
		adf2008c01v1L2rOut3Src OBJECT-TYPE
			SYNTAX Hde2L2rSrcA
			MAX-ACCESS read-write
			STATUS current
			DESCRIPTION
				"Insertion source used in L2R OUT channel 3"
		::= { adf2008c01v1Entry 45 }

		-- 1.3.6.1.4.1.10106.3.101291.1.1.47
		adf2008c01v1L2rOut4Src OBJECT-TYPE
			SYNTAX Hde2L2rSrcA
			MAX-ACCESS read-write
			STATUS current
			DESCRIPTION
				"Insertion source used in L2R OUT channel 4"
		::= { adf2008c01v1Entry 47 }

		-- 1.3.6.1.4.1.10106.3.101291.1.1.49
		adf2008c01v1L2rOut5Src OBJECT-TYPE
			SYNTAX Hde2L2rSrcA
			MAX-ACCESS read-write
			STATUS current
			DESCRIPTION
				"Insertion source used in L2R OUT channel 5"
		::= { adf2008c01v1Entry 49 }

		-- 1.3.6.1.4.1.10106.3.101291.1.1.51
		adf2008c01v1L2rOut6Src OBJECT-TYPE
			SYNTAX Hde2L2rSrcA
			MAX-ACCESS read-write
			STATUS current
			DESCRIPTION
				"Insertion source used in L2R OUT channel 6"
		::= { adf2008c01v1Entry 51 }

		-- 1.3.6.1.4.1.10106.3.101291.1.1.53
		adf2008c01v1L2rOut7Src OBJECT-TYPE
			SYNTAX Hde2L2rSrcA
			MAX-ACCESS read-write
			STATUS current
			DESCRIPTION
				"Insertion source used in L2R OUT channel 7"
		::= { adf2008c01v1Entry 53 }

		-- 1.3.6.1.4.1.10106.3.101291.1.1.55
		adf2008c01v1L2rOut8Src OBJECT-TYPE
			SYNTAX Hde2L2rSrcA
			MAX-ACCESS read-write
			STATUS current
			DESCRIPTION
				"Insertion source used in L2R OUT channel 8"
		::= { adf2008c01v1Entry 55 }

		-- 1.3.6.1.4.1.10106.3.101291.1.1.57
		adf2008c01v1L2rOut9Src OBJECT-TYPE
			SYNTAX Hde2L2rSrcA
			MAX-ACCESS read-write
			STATUS current
			DESCRIPTION
				"Insertion source used in L2R OUT channel 9"
		::= { adf2008c01v1Entry 57 }

		-- 1.3.6.1.4.1.10106.3.101291.1.1.59
		adf2008c01v1L2rOut10Src OBJECT-TYPE
			SYNTAX Hde2L2rSrcA
			MAX-ACCESS read-write
			STATUS current
			DESCRIPTION
				"Insertion source used in L2R OUT channel 10"
		::= { adf2008c01v1Entry 59 }

		-- 1.3.6.1.4.1.10106.3.101291.1.1.61
		adf2008c01v1L2rOut11Src OBJECT-TYPE
			SYNTAX Hde2L2rSrcA
			MAX-ACCESS read-write
			STATUS current
			DESCRIPTION
				"Insertion source used in L2R OUT channel 11"
		::= { adf2008c01v1Entry 61 }

		-- 1.3.6.1.4.1.10106.3.101291.1.1.63
		adf2008c01v1L2rOut12Src OBJECT-TYPE
			SYNTAX Hde2L2rSrcA
			MAX-ACCESS read-write
			STATUS current
			DESCRIPTION
				"Insertion source used in L2R OUT channel 12"
		::= { adf2008c01v1Entry 63 }

		-- 1.3.6.1.4.1.10106.3.101291.1.1.65
		adf2008c01v1L2rOut13Src OBJECT-TYPE
			SYNTAX Hde2L2rSrcA
			MAX-ACCESS read-write
			STATUS current
			DESCRIPTION
				"Insertion source used in L2R OUT channel 13"
		::= { adf2008c01v1Entry 65 }

		-- 1.3.6.1.4.1.10106.3.101291.1.1.67
		adf2008c01v1L2rOut14Src OBJECT-TYPE
			SYNTAX Hde2L2rSrcA
			MAX-ACCESS read-write
			STATUS current
			DESCRIPTION
				"Insertion source used in L2R OUT channel 14"
		::= { adf2008c01v1Entry 67 }

		-- 1.3.6.1.4.1.10106.3.101291.1.1.69
		adf2008c01v1L2rOut15Src OBJECT-TYPE
			SYNTAX Hde2L2rSrcA
			MAX-ACCESS read-write
			STATUS current
			DESCRIPTION
				"Insertion source used in L2R OUT channel 15"
		::= { adf2008c01v1Entry 69 }

		-- 1.3.6.1.4.1.10106.3.101291.1.1.71
		adf2008c01v1L2rOut16Src OBJECT-TYPE
			SYNTAX Hde2L2rSrcA
			MAX-ACCESS read-write
			STATUS current
			DESCRIPTION
				"Insertion source used in L2R OUT channel 16"
		::= { adf2008c01v1Entry 71 }

		-- 1.3.6.1.4.1.10106.3.101291.1.1.73
		adf2008c01v1GainIn1 OBJECT-TYPE
			SYNTAX Gain24dbMute
			MAX-ACCESS read-write
			STATUS current
			DESCRIPTION
				"Analog in 1 gain"
		::= { adf2008c01v1Entry 73 }

		-- 1.3.6.1.4.1.10106.3.101291.1.1.75
		adf2008c01v1GainIn2 OBJECT-TYPE
			SYNTAX Gain24dbMute
			MAX-ACCESS read-write
			STATUS current
			DESCRIPTION
				"Analog in 2 gain"
		::= { adf2008c01v1Entry 75 }

		-- 1.3.6.1.4.1.10106.3.101291.1.1.77
		adf2008c01v1GainIn3 OBJECT-TYPE
			SYNTAX Gain24dbMute
			MAX-ACCESS read-write
			STATUS current
			DESCRIPTION
				"Analog in 3 gain"
		::= { adf2008c01v1Entry 77 }

		-- 1.3.6.1.4.1.10106.3.101291.1.1.79
		adf2008c01v1GainIn4 OBJECT-TYPE
			SYNTAX Gain24dbMute
			MAX-ACCESS read-write
			STATUS current
			DESCRIPTION
				"Analog in 4 gain"
		::= { adf2008c01v1Entry 79 }

		-- 1.3.6.1.4.1.10106.3.101291.1.1.81
		adf2008c01v1GainIn5 OBJECT-TYPE
			SYNTAX Gain24dbMute
			MAX-ACCESS read-write
			STATUS current
			DESCRIPTION
				"Analog in 5 gain"
		::= { adf2008c01v1Entry 81 }

		-- 1.3.6.1.4.1.10106.3.101291.1.1.83
		adf2008c01v1GainIn6 OBJECT-TYPE
			SYNTAX Gain24dbMute
			MAX-ACCESS read-write
			STATUS current
			DESCRIPTION
				"Analog in 6 gain"
		::= { adf2008c01v1Entry 83 }

		-- 1.3.6.1.4.1.10106.3.101291.1.1.85
		adf2008c01v1GainIn7 OBJECT-TYPE
			SYNTAX Gain24dbMute
			MAX-ACCESS read-write
			STATUS current
			DESCRIPTION
				"Analog in 7 gain"
		::= { adf2008c01v1Entry 85 }

		-- 1.3.6.1.4.1.10106.3.101291.1.1.87
		adf2008c01v1GainIn8 OBJECT-TYPE
			SYNTAX Gain24dbMute
			MAX-ACCESS read-write
			STATUS current
			DESCRIPTION
				"Analog in 8 gain"
		::= { adf2008c01v1Entry 87 }

		-- 1.3.6.1.4.1.10106.3.101291.1.1.89
		adf2008c01v1AnalogIn1Level OBJECT-TYPE
			SYNTAX LevelDbfsA
			MAX-ACCESS read-only
			STATUS current
			DESCRIPTION
				"Analog in 1 level"
		::= { adf2008c01v1Entry 89 }

		-- 1.3.6.1.4.1.10106.3.101291.1.1.91
		adf2008c01v1AnalogIn2Level OBJECT-TYPE
			SYNTAX LevelDbfsA
			MAX-ACCESS read-only
			STATUS current
			DESCRIPTION
				"Analog in 2 level"
		::= { adf2008c01v1Entry 91 }

		-- 1.3.6.1.4.1.10106.3.101291.1.1.93
		adf2008c01v1AnalogIn3Level OBJECT-TYPE
			SYNTAX LevelDbfsA
			MAX-ACCESS read-only
			STATUS current
			DESCRIPTION
				"Analog in 3 level"
		::= { adf2008c01v1Entry 93 }

		-- 1.3.6.1.4.1.10106.3.101291.1.1.95
		adf2008c01v1AnalogIn4Level OBJECT-TYPE
			SYNTAX LevelDbfsA
			MAX-ACCESS read-only
			STATUS current
			DESCRIPTION
				"Analog in 4 level"
		::= { adf2008c01v1Entry 95 }

		-- 1.3.6.1.4.1.10106.3.101291.1.1.97
		adf2008c01v1AnalogIn5Level OBJECT-TYPE
			SYNTAX LevelDbfsA
			MAX-ACCESS read-only
			STATUS current
			DESCRIPTION
				"Analog in 5 level"
		::= { adf2008c01v1Entry 97 }

		-- 1.3.6.1.4.1.10106.3.101291.1.1.99
		adf2008c01v1AnalogIn6Level OBJECT-TYPE
			SYNTAX LevelDbfsA
			MAX-ACCESS read-only
			STATUS current
			DESCRIPTION
				"Analog in 6 level"
		::= { adf2008c01v1Entry 99 }

		-- 1.3.6.1.4.1.10106.3.101291.1.1.101
		adf2008c01v1AnalogIn7Level OBJECT-TYPE
			SYNTAX LevelDbfsA
			MAX-ACCESS read-only
			STATUS current
			DESCRIPTION
				"Analog in 7 level"
		::= { adf2008c01v1Entry 101 }

		-- 1.3.6.1.4.1.10106.3.101291.1.1.103
		adf2008c01v1AnalogIn8Level OBJECT-TYPE
			SYNTAX LevelDbfsA
			MAX-ACCESS read-only
			STATUS current
			DESCRIPTION
				"Analog in 8 level"
		::= { adf2008c01v1Entry 103 }

		-- 1.3.6.1.4.1.10106.3.101291.1.1.105
		adf2008c01v1BackplaneLocked OBJECT-TYPE
			SYNTAX BitFailN
			MAX-ACCESS read-only
			STATUS current
			DESCRIPTION
				"Locked to internal bus audio (MCLK and WCLK valid and locked)"
		::= { adf2008c01v1Entry 105 }

		-- 1.3.6.1.4.1.10106.3.101291.1.1.106
		adf2008c01v1BackplaneLockedTrapEnable OBJECT-TYPE
			SYNTAX AlarmEnable
			MAX-ACCESS read-write
			STATUS current
			DESCRIPTION
				"Locked to internal bus audio (MCLK and WCLK valid and locked) Trap Enable"
		::= { adf2008c01v1Entry 106 }

		-- 1.3.6.1.4.1.10106.3.101291.1.1.107
		adf2008c01v1L2rIn1Pres OBJECT-TYPE
			SYNTAX BitFailN
			MAX-ACCESS read-only
			STATUS current
			DESCRIPTION
				"There is a valid audio signal in channel 1 of  L2R IN"
		::= { adf2008c01v1Entry 107 }

		-- 1.3.6.1.4.1.10106.3.101291.1.1.109
		adf2008c01v1L2rIn2Pres OBJECT-TYPE
			SYNTAX BitFailN
			MAX-ACCESS read-only
			STATUS current
			DESCRIPTION
				"There is a valid audio signal in channel 2 of  L2R IN"
		::= { adf2008c01v1Entry 109 }

		-- 1.3.6.1.4.1.10106.3.101291.1.1.111
		adf2008c01v1L2rIn3Pres OBJECT-TYPE
			SYNTAX BitFailN
			MAX-ACCESS read-only
			STATUS current
			DESCRIPTION
				"There is a valid audio signal in channel 3 of  L2R IN"
		::= { adf2008c01v1Entry 111 }

		-- 1.3.6.1.4.1.10106.3.101291.1.1.113
		adf2008c01v1L2rIn4Pres OBJECT-TYPE
			SYNTAX BitFailN
			MAX-ACCESS read-only
			STATUS current
			DESCRIPTION
				"There is a valid audio signal in channel 4 of  L2R IN"
		::= { adf2008c01v1Entry 113 }

		-- 1.3.6.1.4.1.10106.3.101291.1.1.115
		adf2008c01v1L2rIn5Pres OBJECT-TYPE
			SYNTAX BitFailN
			MAX-ACCESS read-only
			STATUS current
			DESCRIPTION
				"There is a valid audio signal in channel 5 of  L2R IN"
		::= { adf2008c01v1Entry 115 }

		-- 1.3.6.1.4.1.10106.3.101291.1.1.117
		adf2008c01v1L2rIn6Pres OBJECT-TYPE
			SYNTAX BitFailN
			MAX-ACCESS read-only
			STATUS current
			DESCRIPTION
				"There is a valid audio signal in channel 6 of  L2R IN"
		::= { adf2008c01v1Entry 117 }

		-- 1.3.6.1.4.1.10106.3.101291.1.1.119
		adf2008c01v1L2rIn7Pres OBJECT-TYPE
			SYNTAX BitFailN
			MAX-ACCESS read-only
			STATUS current
			DESCRIPTION
				"There is a valid audio signal in channel 7 of  L2R IN"
		::= { adf2008c01v1Entry 119 }

		-- 1.3.6.1.4.1.10106.3.101291.1.1.121
		adf2008c01v1L2rIn8Pres OBJECT-TYPE
			SYNTAX BitFailN
			MAX-ACCESS read-only
			STATUS current
			DESCRIPTION
				"There is a valid audio signal in channel 8 of  L2R IN"
		::= { adf2008c01v1Entry 121 }

		-- 1.3.6.1.4.1.10106.3.101291.1.1.123
		adf2008c01v1L2rIn9Pres OBJECT-TYPE
			SYNTAX BitFailN
			MAX-ACCESS read-only
			STATUS current
			DESCRIPTION
				"There is a valid audio signal in channel 9 of  L2R IN"
		::= { adf2008c01v1Entry 123 }

		-- 1.3.6.1.4.1.10106.3.101291.1.1.125
		adf2008c01v1L2rIn10Pres OBJECT-TYPE
			SYNTAX BitFailN
			MAX-ACCESS read-only
			STATUS current
			DESCRIPTION
				"There is a valid audio signal in channel 10 of  L2R IN"
		::= { adf2008c01v1Entry 125 }

		-- 1.3.6.1.4.1.10106.3.101291.1.1.127
		adf2008c01v1L2rIn11Pres OBJECT-TYPE
			SYNTAX BitFailN
			MAX-ACCESS read-only
			STATUS current
			DESCRIPTION
				"There is a valid audio signal in channel 11 of  L2R IN"
		::= { adf2008c01v1Entry 127 }

		-- 1.3.6.1.4.1.10106.3.101291.1.1.129
		adf2008c01v1L2rIn12Pres OBJECT-TYPE
			SYNTAX BitFailN
			MAX-ACCESS read-only
			STATUS current
			DESCRIPTION
				"There is a valid audio signal in channel 12 of  L2R IN"
		::= { adf2008c01v1Entry 129 }

		-- 1.3.6.1.4.1.10106.3.101291.1.1.131
		adf2008c01v1L2rIn13Pres OBJECT-TYPE
			SYNTAX BitFailN
			MAX-ACCESS read-only
			STATUS current
			DESCRIPTION
				"There is a valid audio signal in channel 13 of  L2R IN"
		::= { adf2008c01v1Entry 131 }

		-- 1.3.6.1.4.1.10106.3.101291.1.1.133
		adf2008c01v1L2rIn14Pres OBJECT-TYPE
			SYNTAX BitFailN
			MAX-ACCESS read-only
			STATUS current
			DESCRIPTION
				"There is a valid audio signal in channel 14 of  L2R IN"
		::= { adf2008c01v1Entry 133 }

		-- 1.3.6.1.4.1.10106.3.101291.1.1.135
		adf2008c01v1L2rIn15Pres OBJECT-TYPE
			SYNTAX BitFailN
			MAX-ACCESS read-only
			STATUS current
			DESCRIPTION
				"There is a valid audio signal in channel 15 of  L2R IN"
		::= { adf2008c01v1Entry 135 }

		-- 1.3.6.1.4.1.10106.3.101291.1.1.137
		adf2008c01v1L2rIn16Pres OBJECT-TYPE
			SYNTAX BitFailN
			MAX-ACCESS read-only
			STATUS current
			DESCRIPTION
				"There is a valid audio signal in channel 16 of  L2R IN"
		::= { adf2008c01v1Entry 137 }

		-- 1.3.6.1.4.1.10106.3.101291.1.1.139
		adf2008c01v1R2lIn1Pres OBJECT-TYPE
			SYNTAX BitFailN
			MAX-ACCESS read-only
			STATUS current
			DESCRIPTION
				"There is a valid audio signal in channel 1 of  R2L IN"
		::= { adf2008c01v1Entry 139 }

		-- 1.3.6.1.4.1.10106.3.101291.1.1.141
		adf2008c01v1R2lIn2Pres OBJECT-TYPE
			SYNTAX BitFailN
			MAX-ACCESS read-only
			STATUS current
			DESCRIPTION
				"There is a valid audio signal in channel 2 of  R2L IN"
		::= { adf2008c01v1Entry 141 }

		-- 1.3.6.1.4.1.10106.3.101291.1.1.143
		adf2008c01v1R2lIn3Pres OBJECT-TYPE
			SYNTAX BitFailN
			MAX-ACCESS read-only
			STATUS current
			DESCRIPTION
				"There is a valid audio signal in channel 3 of  R2L IN"
		::= { adf2008c01v1Entry 143 }

		-- 1.3.6.1.4.1.10106.3.101291.1.1.145
		adf2008c01v1R2lIn4Pres OBJECT-TYPE
			SYNTAX BitFailN
			MAX-ACCESS read-only
			STATUS current
			DESCRIPTION
				"There is a valid audio signal in channel 4 of  R2L IN"
		::= { adf2008c01v1Entry 145 }

		-- 1.3.6.1.4.1.10106.3.101291.1.1.147
		adf2008c01v1R2lIn5Pres OBJECT-TYPE
			SYNTAX BitFailN
			MAX-ACCESS read-only
			STATUS current
			DESCRIPTION
				"There is a valid audio signal in channel 5 of  R2L IN"
		::= { adf2008c01v1Entry 147 }

		-- 1.3.6.1.4.1.10106.3.101291.1.1.149
		adf2008c01v1R2lIn6Pres OBJECT-TYPE
			SYNTAX BitFailN
			MAX-ACCESS read-only
			STATUS current
			DESCRIPTION
				"There is a valid audio signal in channel 6 of  R2L IN"
		::= { adf2008c01v1Entry 149 }

		-- 1.3.6.1.4.1.10106.3.101291.1.1.151
		adf2008c01v1R2lIn7Pres OBJECT-TYPE
			SYNTAX BitFailN
			MAX-ACCESS read-only
			STATUS current
			DESCRIPTION
				"There is a valid audio signal in channel 7 of  R2L IN"
		::= { adf2008c01v1Entry 151 }

		-- 1.3.6.1.4.1.10106.3.101291.1.1.153
		adf2008c01v1R2lIn8Pres OBJECT-TYPE
			SYNTAX BitFailN
			MAX-ACCESS read-only
			STATUS current
			DESCRIPTION
				"There is a valid audio signal in channel 8 of  R2L IN"
		::= { adf2008c01v1Entry 153 }

		-- 1.3.6.1.4.1.10106.3.101291.1.1.155
		adf2008c01v1R2lIn9Pres OBJECT-TYPE
			SYNTAX BitFailN
			MAX-ACCESS read-only
			STATUS current
			DESCRIPTION
				"There is a valid audio signal in channel 9 of  R2L IN"
		::= { adf2008c01v1Entry 155 }

		-- 1.3.6.1.4.1.10106.3.101291.1.1.157
		adf2008c01v1R2lIn10Pres OBJECT-TYPE
			SYNTAX BitFailN
			MAX-ACCESS read-only
			STATUS current
			DESCRIPTION
				"There is a valid audio signal in channel 10 of  R2L IN"
		::= { adf2008c01v1Entry 157 }

		-- 1.3.6.1.4.1.10106.3.101291.1.1.159
		adf2008c01v1R2lIn11Pres OBJECT-TYPE
			SYNTAX BitFailN
			MAX-ACCESS read-only
			STATUS current
			DESCRIPTION
				"There is a valid audio signal in channel 11 of  R2L IN"
		::= { adf2008c01v1Entry 159 }

		-- 1.3.6.1.4.1.10106.3.101291.1.1.161
		adf2008c01v1R2lIn12Pres OBJECT-TYPE
			SYNTAX BitFailN
			MAX-ACCESS read-only
			STATUS current
			DESCRIPTION
				"There is a valid audio signal in channel 12 of  R2L IN"
		::= { adf2008c01v1Entry 161 }

		-- 1.3.6.1.4.1.10106.3.101291.1.1.163
		adf2008c01v1R2lIn13Pres OBJECT-TYPE
			SYNTAX BitFailN
			MAX-ACCESS read-only
			STATUS current
			DESCRIPTION
				"There is a valid audio signal in channel 13 of  R2L IN"
		::= { adf2008c01v1Entry 163 }

		-- 1.3.6.1.4.1.10106.3.101291.1.1.165
		adf2008c01v1R2lIn14Pres OBJECT-TYPE
			SYNTAX BitFailN
			MAX-ACCESS read-only
			STATUS current
			DESCRIPTION
				"There is a valid audio signal in channel 14 of  R2L IN"
		::= { adf2008c01v1Entry 165 }

		-- 1.3.6.1.4.1.10106.3.101291.1.1.167
		adf2008c01v1R2lIn15Pres OBJECT-TYPE
			SYNTAX BitFailN
			MAX-ACCESS read-only
			STATUS current
			DESCRIPTION
				"There is a valid audio signal in channel 15 of  R2L IN"
		::= { adf2008c01v1Entry 167 }

		-- 1.3.6.1.4.1.10106.3.101291.1.1.169
		adf2008c01v1R2lIn16Pres OBJECT-TYPE
			SYNTAX BitFailN
			MAX-ACCESS read-only
			STATUS current
			DESCRIPTION
				"There is a valid audio signal in channel 16 of  R2L IN"
		::= { adf2008c01v1Entry 169 }

		-- 1.3.6.1.4.1.10106.3.101291.1.1.171
		adf2008c01v1AnalogInOverfl OBJECT-TYPE
			SYNTAX BitFail
			MAX-ACCESS read-only
			STATUS current
			DESCRIPTION
				"Analog inputs overflow"
		::= { adf2008c01v1Entry 171 }

		-- 1.3.6.1.4.1.10106.3.101291.1.1.172
		adf2008c01v1AnalogInOverflTrapEnable OBJECT-TYPE
			SYNTAX AlarmEnable
			MAX-ACCESS read-write
			STATUS current
			DESCRIPTION
				"Analog inputs overflow Trap Enable"
		::= { adf2008c01v1Entry 172 }

		-- 1.3.6.1.4.1.10106.3.101291.1.1.173
		adf2008c01v1SerialNo OBJECT-TYPE
			SYNTAX SerialNo
			MAX-ACCESS read-only
			STATUS current
			DESCRIPTION
				"Serial number"
		::= { adf2008c01v1Entry 173 }

		-- 1.3.6.1.4.1.10106.3.101291.1.1.175
		adf2008c01v1OverloadAlarm1 OBJECT-TYPE
			SYNTAX BitFail
			MAX-ACCESS read-only
			STATUS current
			DESCRIPTION
				"Analog in 1 overload fail"
		::= { adf2008c01v1Entry 175 }

		-- 1.3.6.1.4.1.10106.3.101291.1.1.177
		adf2008c01v1OverloadAlarm2 OBJECT-TYPE
			SYNTAX BitFail
			MAX-ACCESS read-only
			STATUS current
			DESCRIPTION
				"Analog in 2 overload fail"
		::= { adf2008c01v1Entry 177 }

		-- 1.3.6.1.4.1.10106.3.101291.1.1.179
		adf2008c01v1OverloadAlarm3 OBJECT-TYPE
			SYNTAX BitFail
			MAX-ACCESS read-only
			STATUS current
			DESCRIPTION
				"Analog in 3 overload fail"
		::= { adf2008c01v1Entry 179 }

		-- 1.3.6.1.4.1.10106.3.101291.1.1.181
		adf2008c01v1OverloadAlarm4 OBJECT-TYPE
			SYNTAX BitFail
			MAX-ACCESS read-only
			STATUS current
			DESCRIPTION
				"Analog in 4 overload fail"
		::= { adf2008c01v1Entry 181 }

		-- 1.3.6.1.4.1.10106.3.101291.1.1.183
		adf2008c01v1OverloadAlarm5 OBJECT-TYPE
			SYNTAX BitFail
			MAX-ACCESS read-only
			STATUS current
			DESCRIPTION
				"Analog in 5 overload fail"
		::= { adf2008c01v1Entry 183 }

		-- 1.3.6.1.4.1.10106.3.101291.1.1.185
		adf2008c01v1OverloadAlarm6 OBJECT-TYPE
			SYNTAX BitFail
			MAX-ACCESS read-only
			STATUS current
			DESCRIPTION
				"Analog in 6 overload fail"
		::= { adf2008c01v1Entry 185 }

		-- 1.3.6.1.4.1.10106.3.101291.1.1.187
		adf2008c01v1OverloadAlarm7 OBJECT-TYPE
			SYNTAX BitFail
			MAX-ACCESS read-only
			STATUS current
			DESCRIPTION
				"Analog in 7 overload fail"
		::= { adf2008c01v1Entry 187 }

		-- 1.3.6.1.4.1.10106.3.101291.1.1.189
		adf2008c01v1OverloadAlarm8 OBJECT-TYPE
			SYNTAX BitFail
			MAX-ACCESS read-only
			STATUS current
			DESCRIPTION
				"Analog in 8 overload fail"
		::= { adf2008c01v1Entry 189 }

		-- 1.3.6.1.4.1.10106.3.474801
		daf2008c01v1 OBJECT IDENTIFIER ::= { albalaProducts 474801 }

		-- 1.3.6.1.4.1.10106.3.474801.1
		daf2008c01v1Table  OBJECT-TYPE
			SYNTAX SEQUENCE OF Daf2008c01v1Entry
			MAX-ACCESS not-accessible
			STATUS current
			DESCRIPTION
				"Module  DAF2008C01V1 Table"
			::= { daf2008c01v1 1 }

		-- 1.3.6.1.4.1.10106.3.474801.1.1
		daf2008c01v1Entry  OBJECT-TYPE
			SYNTAX Daf2008c01v1Entry
			MAX-ACCESS not-accessible
			STATUS current
			DESCRIPTION
				"Module DAF2008C01V1 Entry"
			INDEX { daf2008c01v1Index }
			::= { daf2008c01v1Table 1 }

			Daf2008c01v1Entry ::=
			SEQUENCE {
				daf2008c01v1Index
				ModuleIndex,
				daf2008c01v1ActivePreset
				Preset16Active,
				daf2008c01v1LoadPreset
				Preset16Load,
				daf2008c01v1SavePreset
				Preset16Save,
				daf2008c01v1AudioFailMode
				AudioFailMode,
				daf2008c01v1Aes1LOutSrc
				Hde2AesSrc,
				daf2008c01v1Aes1ROutSrc
				Hde2AesSrc,
				daf2008c01v1Aes2LOutSrc
				Hde2AesSrc,
				daf2008c01v1Aes2ROutSrc
				Hde2AesSrc,
				daf2008c01v1Aes3LOutSrc
				Hde2AesSrc,
				daf2008c01v1Aes3ROutSrc
				Hde2AesSrc,
				daf2008c01v1Aes4LOutSrc
				Hde2AesSrc,
				daf2008c01v1Aes4ROutSrc
				Hde2AesSrc,
				daf2008c01v1GainOut1
				Gain24dbMute,
				daf2008c01v1GainOut2
				Gain24dbMute,
				daf2008c01v1GainOut3
				Gain24dbMute,
				daf2008c01v1GainOut4
				Gain24dbMute,
				daf2008c01v1GainOut5
				Gain24dbMute,
				daf2008c01v1GainOut6
				Gain24dbMute,
				daf2008c01v1GainOut7
				Gain24dbMute,
				daf2008c01v1GainOut8
				Gain24dbMute,
				daf2008c01v1AesOut1Level
				LevelDbfsA,
				daf2008c01v1AesOut2Level
				LevelDbfsA,
				daf2008c01v1AesOut3Level
				LevelDbfsA,
				daf2008c01v1AesOut4Level
				LevelDbfsA,
				daf2008c01v1AesOut5Level
				LevelDbfsA,
				daf2008c01v1AesOut6Level
				LevelDbfsA,
				daf2008c01v1AesOut7Level
				LevelDbfsA,
				daf2008c01v1AesOut8Level
				LevelDbfsA,
				daf2008c01v1BackplaneLocked
				BitFailN,
				daf2008c01v1BackplaneLockedTrapEnable
				AlarmEnable,
				daf2008c01v1L2rIn1Pres
				BitFailN,
				daf2008c01v1L2rIn2Pres
				BitFailN,
				daf2008c01v1L2rIn3Pres
				BitFailN,
				daf2008c01v1L2rIn4Pres
				BitFailN,
				daf2008c01v1L2rIn5Pres
				BitFailN,
				daf2008c01v1L2rIn6Pres
				BitFailN,
				daf2008c01v1L2rIn7Pres
				BitFailN,
				daf2008c01v1L2rIn8Pres
				BitFailN,
				daf2008c01v1L2rIn9Pres
				BitFailN,
				daf2008c01v1L2rIn10Pres
				BitFailN,
				daf2008c01v1L2rIn11Pres
				BitFailN,
				daf2008c01v1L2rIn12Pres
				BitFailN,
				daf2008c01v1L2rIn13Pres
				BitFailN,
				daf2008c01v1L2rIn14Pres
				BitFailN,
				daf2008c01v1L2rIn15Pres
				BitFailN,
				daf2008c01v1L2rIn16Pres
				BitFailN,
				daf2008c01v1R2lIn1Pres
				BitFailN,
				daf2008c01v1R2lIn2Pres
				BitFailN,
				daf2008c01v1R2lIn3Pres
				BitFailN,
				daf2008c01v1R2lIn4Pres
				BitFailN,
				daf2008c01v1R2lIn5Pres
				BitFailN,
				daf2008c01v1R2lIn6Pres
				BitFailN,
				daf2008c01v1R2lIn7Pres
				BitFailN,
				daf2008c01v1R2lIn8Pres
				BitFailN,
				daf2008c01v1R2lIn9Pres
				BitFailN,
				daf2008c01v1R2lIn10Pres
				BitFailN,
				daf2008c01v1R2lIn11Pres
				BitFailN,
				daf2008c01v1R2lIn12Pres
				BitFailN,
				daf2008c01v1R2lIn13Pres
				BitFailN,
				daf2008c01v1R2lIn14Pres
				BitFailN,
				daf2008c01v1R2lIn15Pres
				BitFailN,
				daf2008c01v1R2lIn16Pres
				BitFailN,
				daf2008c01v1SerialNo
				SerialNo,
				daf2008c01v1OverloadAlarm1
				BitFail,
				daf2008c01v1OverloadAlarm2
				BitFail,
				daf2008c01v1OverloadAlarm3
				BitFail,
				daf2008c01v1OverloadAlarm4
				BitFail,
				daf2008c01v1OverloadAlarm5
				BitFail,
				daf2008c01v1OverloadAlarm6
				BitFail,
				daf2008c01v1OverloadAlarm7
				BitFail,
				daf2008c01v1OverloadAlarm8
				BitFail
			 }

		-- 1.3.6.1.4.1.10106.3.101291.1.1.1
		daf2008c01v1Index OBJECT-TYPE
			SYNTAX ModuleIndex
			MAX-ACCESS read-only
			STATUS current
			DESCRIPTION
				"Index of DAF2008C01V1 Table"
		::= { daf2008c01v1Entry 1 }

		-- 1.3.6.1.4.1.10106.3.101291.1.1.3
		daf2008c01v1ActivePreset OBJECT-TYPE
			SYNTAX Preset16Active
			MAX-ACCESS read-only
			STATUS current
			DESCRIPTION
				"Shows the active preset"
		::= { daf2008c01v1Entry 3 }

		-- 1.3.6.1.4.1.10106.3.101291.1.1.5
		daf2008c01v1LoadPreset OBJECT-TYPE
			SYNTAX Preset16Load
			MAX-ACCESS read-write
			STATUS current
			DESCRIPTION
				"Allows loading a preset"
		::= { daf2008c01v1Entry 5 }

		-- 1.3.6.1.4.1.10106.3.101291.1.1.7
		daf2008c01v1SavePreset OBJECT-TYPE
			SYNTAX Preset16Save
			MAX-ACCESS read-write
			STATUS current
			DESCRIPTION
				"Allows saving a preset"
		::= { daf2008c01v1Entry 7 }

		-- 1.3.6.1.4.1.10106.3.101291.1.1.9
		daf2008c01v1AudioFailMode OBJECT-TYPE
			SYNTAX AudioFailMode
			MAX-ACCESS read-write
			STATUS current
			DESCRIPTION
				"Allows selecting the output signal when the source signal fails"
		::= { daf2008c01v1Entry 9 }

		-- 1.3.6.1.4.1.10106.3.101291.1.1.11
		daf2008c01v1Aes1LOutSrc OBJECT-TYPE
			SYNTAX Hde2AesSrc
			MAX-ACCESS read-write
			STATUS current
			DESCRIPTION
				"Analog 1 output source (left or right slot)"
		::= { daf2008c01v1Entry 11 }

		-- 1.3.6.1.4.1.10106.3.101291.1.1.13
		daf2008c01v1Aes1ROutSrc OBJECT-TYPE
			SYNTAX Hde2AesSrc
			MAX-ACCESS read-write
			STATUS current
			DESCRIPTION
				"Analog 2 output source (left or right slot)"
		::= { daf2008c01v1Entry 13 }

		-- 1.3.6.1.4.1.10106.3.101291.1.1.15
		daf2008c01v1Aes2LOutSrc OBJECT-TYPE
			SYNTAX Hde2AesSrc
			MAX-ACCESS read-write
			STATUS current
			DESCRIPTION
				"Analog 3 output source (left or right slot)"
		::= { daf2008c01v1Entry 15 }

		-- 1.3.6.1.4.1.10106.3.101291.1.1.17
		daf2008c01v1Aes2ROutSrc OBJECT-TYPE
			SYNTAX Hde2AesSrc
			MAX-ACCESS read-write
			STATUS current
			DESCRIPTION
				"Analog 4 output source (left or right slot)"
		::= { daf2008c01v1Entry 17 }

		-- 1.3.6.1.4.1.10106.3.101291.1.1.19
		daf2008c01v1Aes3LOutSrc OBJECT-TYPE
			SYNTAX Hde2AesSrc
			MAX-ACCESS read-write
			STATUS current
			DESCRIPTION
				"Analog 5 output source (left or right slot)"
		::= { daf2008c01v1Entry 19 }

		-- 1.3.6.1.4.1.10106.3.101291.1.1.21
		daf2008c01v1Aes3ROutSrc OBJECT-TYPE
			SYNTAX Hde2AesSrc
			MAX-ACCESS read-write
			STATUS current
			DESCRIPTION
				"Analog 6 output source (left or right slot)"
		::= { daf2008c01v1Entry 21 }

		-- 1.3.6.1.4.1.10106.3.101291.1.1.23
		daf2008c01v1Aes4LOutSrc OBJECT-TYPE
			SYNTAX Hde2AesSrc
			MAX-ACCESS read-write
			STATUS current
			DESCRIPTION
				"Analog 7 output source (left or right slot)"
		::= { daf2008c01v1Entry 23 }

		-- 1.3.6.1.4.1.10106.3.101291.1.1.25
		daf2008c01v1Aes4ROutSrc OBJECT-TYPE
			SYNTAX Hde2AesSrc
			MAX-ACCESS read-write
			STATUS current
			DESCRIPTION
				"Analog 8 output source (left or right slot)"
		::= { daf2008c01v1Entry 25 }

		-- 1.3.6.1.4.1.10106.3.101291.1.1.27
		daf2008c01v1GainOut1 OBJECT-TYPE
			SYNTAX Gain24dbMute
			MAX-ACCESS read-write
			STATUS current
			DESCRIPTION
				"Analog 1 output gain"
		::= { daf2008c01v1Entry 27 }

		-- 1.3.6.1.4.1.10106.3.101291.1.1.29
		daf2008c01v1GainOut2 OBJECT-TYPE
			SYNTAX Gain24dbMute
			MAX-ACCESS read-write
			STATUS current
			DESCRIPTION
				"Analog 2 output gain"
		::= { daf2008c01v1Entry 29 }

		-- 1.3.6.1.4.1.10106.3.101291.1.1.31
		daf2008c01v1GainOut3 OBJECT-TYPE
			SYNTAX Gain24dbMute
			MAX-ACCESS read-write
			STATUS current
			DESCRIPTION
				"Analog 3 output gain"
		::= { daf2008c01v1Entry 31 }

		-- 1.3.6.1.4.1.10106.3.101291.1.1.33
		daf2008c01v1GainOut4 OBJECT-TYPE
			SYNTAX Gain24dbMute
			MAX-ACCESS read-write
			STATUS current
			DESCRIPTION
				"Analog 4 output gain"
		::= { daf2008c01v1Entry 33 }

		-- 1.3.6.1.4.1.10106.3.101291.1.1.35
		daf2008c01v1GainOut5 OBJECT-TYPE
			SYNTAX Gain24dbMute
			MAX-ACCESS read-write
			STATUS current
			DESCRIPTION
				"Analog 5 output gain"
		::= { daf2008c01v1Entry 35 }

		-- 1.3.6.1.4.1.10106.3.101291.1.1.37
		daf2008c01v1GainOut6 OBJECT-TYPE
			SYNTAX Gain24dbMute
			MAX-ACCESS read-write
			STATUS current
			DESCRIPTION
				"Analog 6 output gain"
		::= { daf2008c01v1Entry 37 }

		-- 1.3.6.1.4.1.10106.3.101291.1.1.39
		daf2008c01v1GainOut7 OBJECT-TYPE
			SYNTAX Gain24dbMute
			MAX-ACCESS read-write
			STATUS current
			DESCRIPTION
				"Analog 7 output gain"
		::= { daf2008c01v1Entry 39 }

		-- 1.3.6.1.4.1.10106.3.101291.1.1.41
		daf2008c01v1GainOut8 OBJECT-TYPE
			SYNTAX Gain24dbMute
			MAX-ACCESS read-write
			STATUS current
			DESCRIPTION
				"Analog 8 output gain"
		::= { daf2008c01v1Entry 41 }

		-- 1.3.6.1.4.1.10106.3.101291.1.1.43
		daf2008c01v1AesOut1Level OBJECT-TYPE
			SYNTAX LevelDbfsA
			MAX-ACCESS read-only
			STATUS current
			DESCRIPTION
				"Analog 1 output level"
		::= { daf2008c01v1Entry 43 }

		-- 1.3.6.1.4.1.10106.3.101291.1.1.45
		daf2008c01v1AesOut2Level OBJECT-TYPE
			SYNTAX LevelDbfsA
			MAX-ACCESS read-only
			STATUS current
			DESCRIPTION
				"Analog 2 output level"
		::= { daf2008c01v1Entry 45 }

		-- 1.3.6.1.4.1.10106.3.101291.1.1.47
		daf2008c01v1AesOut3Level OBJECT-TYPE
			SYNTAX LevelDbfsA
			MAX-ACCESS read-only
			STATUS current
			DESCRIPTION
				"Analog 3 output level"
		::= { daf2008c01v1Entry 47 }

		-- 1.3.6.1.4.1.10106.3.101291.1.1.49
		daf2008c01v1AesOut4Level OBJECT-TYPE
			SYNTAX LevelDbfsA
			MAX-ACCESS read-only
			STATUS current
			DESCRIPTION
				"Analog 4 output level"
		::= { daf2008c01v1Entry 49 }

		-- 1.3.6.1.4.1.10106.3.101291.1.1.51
		daf2008c01v1AesOut5Level OBJECT-TYPE
			SYNTAX LevelDbfsA
			MAX-ACCESS read-only
			STATUS current
			DESCRIPTION
				"Analog 5 output level"
		::= { daf2008c01v1Entry 51 }

		-- 1.3.6.1.4.1.10106.3.101291.1.1.53
		daf2008c01v1AesOut6Level OBJECT-TYPE
			SYNTAX LevelDbfsA
			MAX-ACCESS read-only
			STATUS current
			DESCRIPTION
				"Analog 6 output level"
		::= { daf2008c01v1Entry 53 }

		-- 1.3.6.1.4.1.10106.3.101291.1.1.55
		daf2008c01v1AesOut7Level OBJECT-TYPE
			SYNTAX LevelDbfsA
			MAX-ACCESS read-only
			STATUS current
			DESCRIPTION
				"Analog 7 output level"
		::= { daf2008c01v1Entry 55 }

		-- 1.3.6.1.4.1.10106.3.101291.1.1.57
		daf2008c01v1AesOut8Level OBJECT-TYPE
			SYNTAX LevelDbfsA
			MAX-ACCESS read-only
			STATUS current
			DESCRIPTION
				"Analog 8 output level"
		::= { daf2008c01v1Entry 57 }

		-- 1.3.6.1.4.1.10106.3.101291.1.1.59
		daf2008c01v1BackplaneLocked OBJECT-TYPE
			SYNTAX BitFailN
			MAX-ACCESS read-only
			STATUS current
			DESCRIPTION
				"Locked to internal bus audio (MCLK and WCLK valid and locked)"
		::= { daf2008c01v1Entry 59 }

		-- 1.3.6.1.4.1.10106.3.101291.1.1.60
		daf2008c01v1BackplaneLockedTrapEnable OBJECT-TYPE
			SYNTAX AlarmEnable
			MAX-ACCESS read-write
			STATUS current
			DESCRIPTION
				"Locked to internal bus audio (MCLK and WCLK valid and locked) Trap Enable"
		::= { daf2008c01v1Entry 60 }

		-- 1.3.6.1.4.1.10106.3.101291.1.1.61
		daf2008c01v1L2rIn1Pres OBJECT-TYPE
			SYNTAX BitFailN
			MAX-ACCESS read-only
			STATUS current
			DESCRIPTION
				"There is a valid audio signal in channel 1 of  L2R IN"
		::= { daf2008c01v1Entry 61 }

		-- 1.3.6.1.4.1.10106.3.101291.1.1.63
		daf2008c01v1L2rIn2Pres OBJECT-TYPE
			SYNTAX BitFailN
			MAX-ACCESS read-only
			STATUS current
			DESCRIPTION
				"There is a valid audio signal in channel 2 of  L2R IN"
		::= { daf2008c01v1Entry 63 }

		-- 1.3.6.1.4.1.10106.3.101291.1.1.65
		daf2008c01v1L2rIn3Pres OBJECT-TYPE
			SYNTAX BitFailN
			MAX-ACCESS read-only
			STATUS current
			DESCRIPTION
				"There is a valid audio signal in channel 3 of  L2R IN"
		::= { daf2008c01v1Entry 65 }

		-- 1.3.6.1.4.1.10106.3.101291.1.1.67
		daf2008c01v1L2rIn4Pres OBJECT-TYPE
			SYNTAX BitFailN
			MAX-ACCESS read-only
			STATUS current
			DESCRIPTION
				"There is a valid audio signal in channel 4 of  L2R IN"
		::= { daf2008c01v1Entry 67 }

		-- 1.3.6.1.4.1.10106.3.101291.1.1.69
		daf2008c01v1L2rIn5Pres OBJECT-TYPE
			SYNTAX BitFailN
			MAX-ACCESS read-only
			STATUS current
			DESCRIPTION
				"There is a valid audio signal in channel 5 of  L2R IN"
		::= { daf2008c01v1Entry 69 }

		-- 1.3.6.1.4.1.10106.3.101291.1.1.71
		daf2008c01v1L2rIn6Pres OBJECT-TYPE
			SYNTAX BitFailN
			MAX-ACCESS read-only
			STATUS current
			DESCRIPTION
				"There is a valid audio signal in channel 6 of  L2R IN"
		::= { daf2008c01v1Entry 71 }

		-- 1.3.6.1.4.1.10106.3.101291.1.1.73
		daf2008c01v1L2rIn7Pres OBJECT-TYPE
			SYNTAX BitFailN
			MAX-ACCESS read-only
			STATUS current
			DESCRIPTION
				"There is a valid audio signal in channel 7 of  L2R IN"
		::= { daf2008c01v1Entry 73 }

		-- 1.3.6.1.4.1.10106.3.101291.1.1.75
		daf2008c01v1L2rIn8Pres OBJECT-TYPE
			SYNTAX BitFailN
			MAX-ACCESS read-only
			STATUS current
			DESCRIPTION
				"There is a valid audio signal in channel 8 of  L2R IN"
		::= { daf2008c01v1Entry 75 }

		-- 1.3.6.1.4.1.10106.3.101291.1.1.77
		daf2008c01v1L2rIn9Pres OBJECT-TYPE
			SYNTAX BitFailN
			MAX-ACCESS read-only
			STATUS current
			DESCRIPTION
				"There is a valid audio signal in channel 9 of  L2R IN"
		::= { daf2008c01v1Entry 77 }

		-- 1.3.6.1.4.1.10106.3.101291.1.1.79
		daf2008c01v1L2rIn10Pres OBJECT-TYPE
			SYNTAX BitFailN
			MAX-ACCESS read-only
			STATUS current
			DESCRIPTION
				"There is a valid audio signal in channel 10 of  L2R IN"
		::= { daf2008c01v1Entry 79 }

		-- 1.3.6.1.4.1.10106.3.101291.1.1.81
		daf2008c01v1L2rIn11Pres OBJECT-TYPE
			SYNTAX BitFailN
			MAX-ACCESS read-only
			STATUS current
			DESCRIPTION
				"There is a valid audio signal in channel 11 of  L2R IN"
		::= { daf2008c01v1Entry 81 }

		-- 1.3.6.1.4.1.10106.3.101291.1.1.83
		daf2008c01v1L2rIn12Pres OBJECT-TYPE
			SYNTAX BitFailN
			MAX-ACCESS read-only
			STATUS current
			DESCRIPTION
				"There is a valid audio signal in channel 12 of  L2R IN"
		::= { daf2008c01v1Entry 83 }

		-- 1.3.6.1.4.1.10106.3.101291.1.1.85
		daf2008c01v1L2rIn13Pres OBJECT-TYPE
			SYNTAX BitFailN
			MAX-ACCESS read-only
			STATUS current
			DESCRIPTION
				"There is a valid audio signal in channel 13 of  L2R IN"
		::= { daf2008c01v1Entry 85 }

		-- 1.3.6.1.4.1.10106.3.101291.1.1.87
		daf2008c01v1L2rIn14Pres OBJECT-TYPE
			SYNTAX BitFailN
			MAX-ACCESS read-only
			STATUS current
			DESCRIPTION
				"There is a valid audio signal in channel 14 of  L2R IN"
		::= { daf2008c01v1Entry 87 }

		-- 1.3.6.1.4.1.10106.3.101291.1.1.89
		daf2008c01v1L2rIn15Pres OBJECT-TYPE
			SYNTAX BitFailN
			MAX-ACCESS read-only
			STATUS current
			DESCRIPTION
				"There is a valid audio signal in channel 15 of  L2R IN"
		::= { daf2008c01v1Entry 89 }

		-- 1.3.6.1.4.1.10106.3.101291.1.1.91
		daf2008c01v1L2rIn16Pres OBJECT-TYPE
			SYNTAX BitFailN
			MAX-ACCESS read-only
			STATUS current
			DESCRIPTION
				"There is a valid audio signal in channel 16 of  L2R IN"
		::= { daf2008c01v1Entry 91 }

		-- 1.3.6.1.4.1.10106.3.101291.1.1.93
		daf2008c01v1R2lIn1Pres OBJECT-TYPE
			SYNTAX BitFailN
			MAX-ACCESS read-only
			STATUS current
			DESCRIPTION
				"There is a valid audio signal in channel 1 of  R2L IN"
		::= { daf2008c01v1Entry 93 }

		-- 1.3.6.1.4.1.10106.3.101291.1.1.95
		daf2008c01v1R2lIn2Pres OBJECT-TYPE
			SYNTAX BitFailN
			MAX-ACCESS read-only
			STATUS current
			DESCRIPTION
				"There is a valid audio signal in channel 2 of  R2L IN"
		::= { daf2008c01v1Entry 95 }

		-- 1.3.6.1.4.1.10106.3.101291.1.1.97
		daf2008c01v1R2lIn3Pres OBJECT-TYPE
			SYNTAX BitFailN
			MAX-ACCESS read-only
			STATUS current
			DESCRIPTION
				"There is a valid audio signal in channel 3 of  R2L IN"
		::= { daf2008c01v1Entry 97 }

		-- 1.3.6.1.4.1.10106.3.101291.1.1.99
		daf2008c01v1R2lIn4Pres OBJECT-TYPE
			SYNTAX BitFailN
			MAX-ACCESS read-only
			STATUS current
			DESCRIPTION
				"There is a valid audio signal in channel 4 of  R2L IN"
		::= { daf2008c01v1Entry 99 }

		-- 1.3.6.1.4.1.10106.3.101291.1.1.101
		daf2008c01v1R2lIn5Pres OBJECT-TYPE
			SYNTAX BitFailN
			MAX-ACCESS read-only
			STATUS current
			DESCRIPTION
				"There is a valid audio signal in channel 5 of  R2L IN"
		::= { daf2008c01v1Entry 101 }

		-- 1.3.6.1.4.1.10106.3.101291.1.1.103
		daf2008c01v1R2lIn6Pres OBJECT-TYPE
			SYNTAX BitFailN
			MAX-ACCESS read-only
			STATUS current
			DESCRIPTION
				"There is a valid audio signal in channel 6 of  R2L IN"
		::= { daf2008c01v1Entry 103 }

		-- 1.3.6.1.4.1.10106.3.101291.1.1.105
		daf2008c01v1R2lIn7Pres OBJECT-TYPE
			SYNTAX BitFailN
			MAX-ACCESS read-only
			STATUS current
			DESCRIPTION
				"There is a valid audio signal in channel 7 of  R2L IN"
		::= { daf2008c01v1Entry 105 }

		-- 1.3.6.1.4.1.10106.3.101291.1.1.107
		daf2008c01v1R2lIn8Pres OBJECT-TYPE
			SYNTAX BitFailN
			MAX-ACCESS read-only
			STATUS current
			DESCRIPTION
				"There is a valid audio signal in channel 8 of  R2L IN"
		::= { daf2008c01v1Entry 107 }

		-- 1.3.6.1.4.1.10106.3.101291.1.1.109
		daf2008c01v1R2lIn9Pres OBJECT-TYPE
			SYNTAX BitFailN
			MAX-ACCESS read-only
			STATUS current
			DESCRIPTION
				"There is a valid audio signal in channel 9 of  R2L IN"
		::= { daf2008c01v1Entry 109 }

		-- 1.3.6.1.4.1.10106.3.101291.1.1.111
		daf2008c01v1R2lIn10Pres OBJECT-TYPE
			SYNTAX BitFailN
			MAX-ACCESS read-only
			STATUS current
			DESCRIPTION
				"There is a valid audio signal in channel 10 of  R2L IN"
		::= { daf2008c01v1Entry 111 }

		-- 1.3.6.1.4.1.10106.3.101291.1.1.113
		daf2008c01v1R2lIn11Pres OBJECT-TYPE
			SYNTAX BitFailN
			MAX-ACCESS read-only
			STATUS current
			DESCRIPTION
				"There is a valid audio signal in channel 11 of  R2L IN"
		::= { daf2008c01v1Entry 113 }

		-- 1.3.6.1.4.1.10106.3.101291.1.1.115
		daf2008c01v1R2lIn12Pres OBJECT-TYPE
			SYNTAX BitFailN
			MAX-ACCESS read-only
			STATUS current
			DESCRIPTION
				"There is a valid audio signal in channel 12 of  R2L IN"
		::= { daf2008c01v1Entry 115 }

		-- 1.3.6.1.4.1.10106.3.101291.1.1.117
		daf2008c01v1R2lIn13Pres OBJECT-TYPE
			SYNTAX BitFailN
			MAX-ACCESS read-only
			STATUS current
			DESCRIPTION
				"There is a valid audio signal in channel 13 of  R2L IN"
		::= { daf2008c01v1Entry 117 }

		-- 1.3.6.1.4.1.10106.3.101291.1.1.119
		daf2008c01v1R2lIn14Pres OBJECT-TYPE
			SYNTAX BitFailN
			MAX-ACCESS read-only
			STATUS current
			DESCRIPTION
				"There is a valid audio signal in channel 14 of  R2L IN"
		::= { daf2008c01v1Entry 119 }

		-- 1.3.6.1.4.1.10106.3.101291.1.1.121
		daf2008c01v1R2lIn15Pres OBJECT-TYPE
			SYNTAX BitFailN
			MAX-ACCESS read-only
			STATUS current
			DESCRIPTION
				"There is a valid audio signal in channel 15 of  R2L IN"
		::= { daf2008c01v1Entry 121 }

		-- 1.3.6.1.4.1.10106.3.101291.1.1.123
		daf2008c01v1R2lIn16Pres OBJECT-TYPE
			SYNTAX BitFailN
			MAX-ACCESS read-only
			STATUS current
			DESCRIPTION
				"There is a valid audio signal in channel 16 of  R2L IN"
		::= { daf2008c01v1Entry 123 }

		-- 1.3.6.1.4.1.10106.3.101291.1.1.125
		daf2008c01v1SerialNo OBJECT-TYPE
			SYNTAX SerialNo
			MAX-ACCESS read-only
			STATUS current
			DESCRIPTION
				"Serial number"
		::= { daf2008c01v1Entry 125 }

		-- 1.3.6.1.4.1.10106.3.101291.1.1.127
		daf2008c01v1OverloadAlarm1 OBJECT-TYPE
			SYNTAX BitFail
			MAX-ACCESS read-only
			STATUS current
			DESCRIPTION
				"Analog out 1 overload fail"
		::= { daf2008c01v1Entry 127 }

		-- 1.3.6.1.4.1.10106.3.101291.1.1.129
		daf2008c01v1OverloadAlarm2 OBJECT-TYPE
			SYNTAX BitFail
			MAX-ACCESS read-only
			STATUS current
			DESCRIPTION
				"Analog out 2 overload fail"
		::= { daf2008c01v1Entry 129 }

		-- 1.3.6.1.4.1.10106.3.101291.1.1.131
		daf2008c01v1OverloadAlarm3 OBJECT-TYPE
			SYNTAX BitFail
			MAX-ACCESS read-only
			STATUS current
			DESCRIPTION
				"Analog out 3 overload fail"
		::= { daf2008c01v1Entry 131 }

		-- 1.3.6.1.4.1.10106.3.101291.1.1.133
		daf2008c01v1OverloadAlarm4 OBJECT-TYPE
			SYNTAX BitFail
			MAX-ACCESS read-only
			STATUS current
			DESCRIPTION
				"Analog out 4 overload fail"
		::= { daf2008c01v1Entry 133 }

		-- 1.3.6.1.4.1.10106.3.101291.1.1.135
		daf2008c01v1OverloadAlarm5 OBJECT-TYPE
			SYNTAX BitFail
			MAX-ACCESS read-only
			STATUS current
			DESCRIPTION
				"Analog out 5 overload fail"
		::= { daf2008c01v1Entry 135 }

		-- 1.3.6.1.4.1.10106.3.101291.1.1.137
		daf2008c01v1OverloadAlarm6 OBJECT-TYPE
			SYNTAX BitFail
			MAX-ACCESS read-only
			STATUS current
			DESCRIPTION
				"Analog out 6 overload fail"
		::= { daf2008c01v1Entry 137 }

		-- 1.3.6.1.4.1.10106.3.101291.1.1.139
		daf2008c01v1OverloadAlarm7 OBJECT-TYPE
			SYNTAX BitFail
			MAX-ACCESS read-only
			STATUS current
			DESCRIPTION
				"Analog out 7 overload fail"
		::= { daf2008c01v1Entry 139 }

		-- 1.3.6.1.4.1.10106.3.101291.1.1.141
		daf2008c01v1OverloadAlarm8 OBJECT-TYPE
			SYNTAX BitFail
			MAX-ACCESS read-only
			STATUS current
			DESCRIPTION
				"Analog out 8 overload fail"
		::= { daf2008c01v1Entry 141 }

		-- 1.3.6.1.4.1.10106.3.478401
		tly3032c04v1 OBJECT IDENTIFIER ::= { albalaProducts 478401 }

		-- 1.3.6.1.4.1.10106.3.478401.1
		tly3032c04v1Table  OBJECT-TYPE
			SYNTAX SEQUENCE OF Tly3032c04v1Entry
			MAX-ACCESS not-accessible
			STATUS current
			DESCRIPTION
				"Module  TLY3032C04V1 Table"
			::= { tly3032c04v1 1 }

		-- 1.3.6.1.4.1.10106.3.478401.1.1
		tly3032c04v1Entry  OBJECT-TYPE
			SYNTAX Tly3032c04v1Entry
			MAX-ACCESS not-accessible
			STATUS current
			DESCRIPTION
				"Module TLY3032C04V1 Entry"
			INDEX { tly3032c04v1Index }
			::= { tly3032c04v1Table 1 }

			Tly3032c04v1Entry ::=
			SEQUENCE {
				tly3032c04v1Index
				ModuleIndex,
				tly3032c04v1Gpi1
				Bit0Ina1Act,
				tly3032c04v1Gpi1TrapEnable
				AlarmEnable,
				tly3032c04v1Gpi2
				Bit0Ina1Act,
				tly3032c04v1Gpi2TrapEnable
				AlarmEnable,
				tly3032c04v1Gpi3
				Bit0Ina1Act,
				tly3032c04v1Gpi3TrapEnable
				AlarmEnable,
				tly3032c04v1Gpi4
				Bit0Ina1Act,
				tly3032c04v1Gpi4TrapEnable
				AlarmEnable,
				tly3032c04v1Gpi5
				Bit0Ina1Act,
				tly3032c04v1Gpi5TrapEnable
				AlarmEnable,
				tly3032c04v1Gpi6
				Bit0Ina1Act,
				tly3032c04v1Gpi6TrapEnable
				AlarmEnable,
				tly3032c04v1Gpi7
				Bit0Ina1Act,
				tly3032c04v1Gpi7TrapEnable
				AlarmEnable,
				tly3032c04v1Gpi8
				Bit0Ina1Act,
				tly3032c04v1Gpi8TrapEnable
				AlarmEnable,
				tly3032c04v1Gpi9
				Bit0Ina1Act,
				tly3032c04v1Gpi9TrapEnable
				AlarmEnable,
				tly3032c04v1Gpi10
				Bit0Ina1Act,
				tly3032c04v1Gpi10TrapEnable
				AlarmEnable,
				tly3032c04v1Gpi11
				Bit0Ina1Act,
				tly3032c04v1Gpi11TrapEnable
				AlarmEnable,
				tly3032c04v1Gpi12
				Bit0Ina1Act,
				tly3032c04v1Gpi12TrapEnable
				AlarmEnable,
				tly3032c04v1Gpi13
				Bit0Ina1Act,
				tly3032c04v1Gpi13TrapEnable
				AlarmEnable,
				tly3032c04v1Gpi14
				Bit0Ina1Act,
				tly3032c04v1Gpi14TrapEnable
				AlarmEnable,
				tly3032c04v1Gpi15
				Bit0Ina1Act,
				tly3032c04v1Gpi15TrapEnable
				AlarmEnable,
				tly3032c04v1Gpi16
				Bit0Ina1Act,
				tly3032c04v1Gpi16TrapEnable
				AlarmEnable,
				tly3032c04v1Gpi17
				Bit0Ina1Act,
				tly3032c04v1Gpi17TrapEnable
				AlarmEnable,
				tly3032c04v1Gpi18
				Bit0Ina1Act,
				tly3032c04v1Gpi18TrapEnable
				AlarmEnable,
				tly3032c04v1Gpi19
				Bit0Ina1Act,
				tly3032c04v1Gpi19TrapEnable
				AlarmEnable,
				tly3032c04v1Gpi20
				Bit0Ina1Act,
				tly3032c04v1Gpi20TrapEnable
				AlarmEnable,
				tly3032c04v1Gpi21
				Bit0Ina1Act,
				tly3032c04v1Gpi21TrapEnable
				AlarmEnable,
				tly3032c04v1Gpi22
				Bit0Ina1Act,
				tly3032c04v1Gpi22TrapEnable
				AlarmEnable,
				tly3032c04v1Gpi23
				Bit0Ina1Act,
				tly3032c04v1Gpi23TrapEnable
				AlarmEnable,
				tly3032c04v1Gpi24
				Bit0Ina1Act,
				tly3032c04v1Gpi24TrapEnable
				AlarmEnable,
				tly3032c04v1Gpi25
				Bit0Ina1Act,
				tly3032c04v1Gpi25TrapEnable
				AlarmEnable,
				tly3032c04v1Gpi26
				Bit0Ina1Act,
				tly3032c04v1Gpi26TrapEnable
				AlarmEnable,
				tly3032c04v1Gpi27
				Bit0Ina1Act,
				tly3032c04v1Gpi27TrapEnable
				AlarmEnable,
				tly3032c04v1Gpi28
				Bit0Ina1Act,
				tly3032c04v1Gpi28TrapEnable
				AlarmEnable,
				tly3032c04v1Gpi29
				Bit0Ina1Act,
				tly3032c04v1Gpi29TrapEnable
				AlarmEnable,
				tly3032c04v1Gpi30
				Bit0Ina1Act,
				tly3032c04v1Gpi30TrapEnable
				AlarmEnable,
				tly3032c04v1Gpi31
				Bit0Ina1Act,
				tly3032c04v1Gpi31TrapEnable
				AlarmEnable,
				tly3032c04v1Gpi32
				Bit0Ina1Act,
				tly3032c04v1Gpi32TrapEnable
				AlarmEnable
			 }

		-- 1.3.6.1.4.1.10106.3.101291.1.1.1
		tly3032c04v1Index OBJECT-TYPE
			SYNTAX ModuleIndex
			MAX-ACCESS read-only
			STATUS current
			DESCRIPTION
				"Index of TLY3032C04V1 Table"
		::= { tly3032c04v1Entry 1 }

		-- 1.3.6.1.4.1.10106.3.101291.1.1.3
		tly3032c04v1Gpi1 OBJECT-TYPE
			SYNTAX Bit0Ina1Act
			MAX-ACCESS read-only
			STATUS current
			DESCRIPTION
				"GPI1 status"
		::= { tly3032c04v1Entry 3 }

		-- 1.3.6.1.4.1.10106.3.101291.1.1.4
		tly3032c04v1Gpi1TrapEnable OBJECT-TYPE
			SYNTAX AlarmEnable
			MAX-ACCESS read-write
			STATUS current
			DESCRIPTION
				"GPI1 status Trap Enable"
		::= { tly3032c04v1Entry 4 }

		-- 1.3.6.1.4.1.10106.3.101291.1.1.5
		tly3032c04v1Gpi2 OBJECT-TYPE
			SYNTAX Bit0Ina1Act
			MAX-ACCESS read-only
			STATUS current
			DESCRIPTION
				"GPI2 status"
		::= { tly3032c04v1Entry 5 }

		-- 1.3.6.1.4.1.10106.3.101291.1.1.6
		tly3032c04v1Gpi2TrapEnable OBJECT-TYPE
			SYNTAX AlarmEnable
			MAX-ACCESS read-write
			STATUS current
			DESCRIPTION
				"GPI2 status Trap Enable"
		::= { tly3032c04v1Entry 6 }

		-- 1.3.6.1.4.1.10106.3.101291.1.1.7
		tly3032c04v1Gpi3 OBJECT-TYPE
			SYNTAX Bit0Ina1Act
			MAX-ACCESS read-only
			STATUS current
			DESCRIPTION
				"GPI3 status"
		::= { tly3032c04v1Entry 7 }

		-- 1.3.6.1.4.1.10106.3.101291.1.1.8
		tly3032c04v1Gpi3TrapEnable OBJECT-TYPE
			SYNTAX AlarmEnable
			MAX-ACCESS read-write
			STATUS current
			DESCRIPTION
				"GPI3 status Trap Enable"
		::= { tly3032c04v1Entry 8 }

		-- 1.3.6.1.4.1.10106.3.101291.1.1.9
		tly3032c04v1Gpi4 OBJECT-TYPE
			SYNTAX Bit0Ina1Act
			MAX-ACCESS read-only
			STATUS current
			DESCRIPTION
				"GPI4 status"
		::= { tly3032c04v1Entry 9 }

		-- 1.3.6.1.4.1.10106.3.101291.1.1.10
		tly3032c04v1Gpi4TrapEnable OBJECT-TYPE
			SYNTAX AlarmEnable
			MAX-ACCESS read-write
			STATUS current
			DESCRIPTION
				"GPI4 status Trap Enable"
		::= { tly3032c04v1Entry 10 }

		-- 1.3.6.1.4.1.10106.3.101291.1.1.11
		tly3032c04v1Gpi5 OBJECT-TYPE
			SYNTAX Bit0Ina1Act
			MAX-ACCESS read-only
			STATUS current
			DESCRIPTION
				"GPI5 status"
		::= { tly3032c04v1Entry 11 }

		-- 1.3.6.1.4.1.10106.3.101291.1.1.12
		tly3032c04v1Gpi5TrapEnable OBJECT-TYPE
			SYNTAX AlarmEnable
			MAX-ACCESS read-write
			STATUS current
			DESCRIPTION
				"GPI5 status Trap Enable"
		::= { tly3032c04v1Entry 12 }

		-- 1.3.6.1.4.1.10106.3.101291.1.1.13
		tly3032c04v1Gpi6 OBJECT-TYPE
			SYNTAX Bit0Ina1Act
			MAX-ACCESS read-only
			STATUS current
			DESCRIPTION
				"GPI6 status"
		::= { tly3032c04v1Entry 13 }

		-- 1.3.6.1.4.1.10106.3.101291.1.1.14
		tly3032c04v1Gpi6TrapEnable OBJECT-TYPE
			SYNTAX AlarmEnable
			MAX-ACCESS read-write
			STATUS current
			DESCRIPTION
				"GPI6 status Trap Enable"
		::= { tly3032c04v1Entry 14 }

		-- 1.3.6.1.4.1.10106.3.101291.1.1.15
		tly3032c04v1Gpi7 OBJECT-TYPE
			SYNTAX Bit0Ina1Act
			MAX-ACCESS read-only
			STATUS current
			DESCRIPTION
				"GPI7 status"
		::= { tly3032c04v1Entry 15 }

		-- 1.3.6.1.4.1.10106.3.101291.1.1.16
		tly3032c04v1Gpi7TrapEnable OBJECT-TYPE
			SYNTAX AlarmEnable
			MAX-ACCESS read-write
			STATUS current
			DESCRIPTION
				"GPI7 status Trap Enable"
		::= { tly3032c04v1Entry 16 }

		-- 1.3.6.1.4.1.10106.3.101291.1.1.17
		tly3032c04v1Gpi8 OBJECT-TYPE
			SYNTAX Bit0Ina1Act
			MAX-ACCESS read-only
			STATUS current
			DESCRIPTION
				"GPI8 status"
		::= { tly3032c04v1Entry 17 }

		-- 1.3.6.1.4.1.10106.3.101291.1.1.18
		tly3032c04v1Gpi8TrapEnable OBJECT-TYPE
			SYNTAX AlarmEnable
			MAX-ACCESS read-write
			STATUS current
			DESCRIPTION
				"GPI8 status Trap Enable"
		::= { tly3032c04v1Entry 18 }

		-- 1.3.6.1.4.1.10106.3.101291.1.1.19
		tly3032c04v1Gpi9 OBJECT-TYPE
			SYNTAX Bit0Ina1Act
			MAX-ACCESS read-only
			STATUS current
			DESCRIPTION
				"GPI9 status"
		::= { tly3032c04v1Entry 19 }

		-- 1.3.6.1.4.1.10106.3.101291.1.1.20
		tly3032c04v1Gpi9TrapEnable OBJECT-TYPE
			SYNTAX AlarmEnable
			MAX-ACCESS read-write
			STATUS current
			DESCRIPTION
				"GPI9 status Trap Enable"
		::= { tly3032c04v1Entry 20 }

		-- 1.3.6.1.4.1.10106.3.101291.1.1.21
		tly3032c04v1Gpi10 OBJECT-TYPE
			SYNTAX Bit0Ina1Act
			MAX-ACCESS read-only
			STATUS current
			DESCRIPTION
				"GPI10 status"
		::= { tly3032c04v1Entry 21 }

		-- 1.3.6.1.4.1.10106.3.101291.1.1.22
		tly3032c04v1Gpi10TrapEnable OBJECT-TYPE
			SYNTAX AlarmEnable
			MAX-ACCESS read-write
			STATUS current
			DESCRIPTION
				"GPI10 status Trap Enable"
		::= { tly3032c04v1Entry 22 }

		-- 1.3.6.1.4.1.10106.3.101291.1.1.23
		tly3032c04v1Gpi11 OBJECT-TYPE
			SYNTAX Bit0Ina1Act
			MAX-ACCESS read-only
			STATUS current
			DESCRIPTION
				"GPI11 status"
		::= { tly3032c04v1Entry 23 }

		-- 1.3.6.1.4.1.10106.3.101291.1.1.24
		tly3032c04v1Gpi11TrapEnable OBJECT-TYPE
			SYNTAX AlarmEnable
			MAX-ACCESS read-write
			STATUS current
			DESCRIPTION
				"GPI11 status Trap Enable"
		::= { tly3032c04v1Entry 24 }

		-- 1.3.6.1.4.1.10106.3.101291.1.1.25
		tly3032c04v1Gpi12 OBJECT-TYPE
			SYNTAX Bit0Ina1Act
			MAX-ACCESS read-only
			STATUS current
			DESCRIPTION
				"GPI12 status"
		::= { tly3032c04v1Entry 25 }

		-- 1.3.6.1.4.1.10106.3.101291.1.1.26
		tly3032c04v1Gpi12TrapEnable OBJECT-TYPE
			SYNTAX AlarmEnable
			MAX-ACCESS read-write
			STATUS current
			DESCRIPTION
				"GPI12 status Trap Enable"
		::= { tly3032c04v1Entry 26 }

		-- 1.3.6.1.4.1.10106.3.101291.1.1.27
		tly3032c04v1Gpi13 OBJECT-TYPE
			SYNTAX Bit0Ina1Act
			MAX-ACCESS read-only
			STATUS current
			DESCRIPTION
				"GPI13 status"
		::= { tly3032c04v1Entry 27 }

		-- 1.3.6.1.4.1.10106.3.101291.1.1.28
		tly3032c04v1Gpi13TrapEnable OBJECT-TYPE
			SYNTAX AlarmEnable
			MAX-ACCESS read-write
			STATUS current
			DESCRIPTION
				"GPI13 status Trap Enable"
		::= { tly3032c04v1Entry 28 }

		-- 1.3.6.1.4.1.10106.3.101291.1.1.29
		tly3032c04v1Gpi14 OBJECT-TYPE
			SYNTAX Bit0Ina1Act
			MAX-ACCESS read-only
			STATUS current
			DESCRIPTION
				"GPI14 status"
		::= { tly3032c04v1Entry 29 }

		-- 1.3.6.1.4.1.10106.3.101291.1.1.30
		tly3032c04v1Gpi14TrapEnable OBJECT-TYPE
			SYNTAX AlarmEnable
			MAX-ACCESS read-write
			STATUS current
			DESCRIPTION
				"GPI14 status Trap Enable"
		::= { tly3032c04v1Entry 30 }

		-- 1.3.6.1.4.1.10106.3.101291.1.1.31
		tly3032c04v1Gpi15 OBJECT-TYPE
			SYNTAX Bit0Ina1Act
			MAX-ACCESS read-only
			STATUS current
			DESCRIPTION
				"GPI15 status"
		::= { tly3032c04v1Entry 31 }

		-- 1.3.6.1.4.1.10106.3.101291.1.1.32
		tly3032c04v1Gpi15TrapEnable OBJECT-TYPE
			SYNTAX AlarmEnable
			MAX-ACCESS read-write
			STATUS current
			DESCRIPTION
				"GPI15 status Trap Enable"
		::= { tly3032c04v1Entry 32 }

		-- 1.3.6.1.4.1.10106.3.101291.1.1.33
		tly3032c04v1Gpi16 OBJECT-TYPE
			SYNTAX Bit0Ina1Act
			MAX-ACCESS read-only
			STATUS current
			DESCRIPTION
				"GPI16 status"
		::= { tly3032c04v1Entry 33 }

		-- 1.3.6.1.4.1.10106.3.101291.1.1.34
		tly3032c04v1Gpi16TrapEnable OBJECT-TYPE
			SYNTAX AlarmEnable
			MAX-ACCESS read-write
			STATUS current
			DESCRIPTION
				"GPI16 status Trap Enable"
		::= { tly3032c04v1Entry 34 }

		-- 1.3.6.1.4.1.10106.3.101291.1.1.35
		tly3032c04v1Gpi17 OBJECT-TYPE
			SYNTAX Bit0Ina1Act
			MAX-ACCESS read-only
			STATUS current
			DESCRIPTION
				"GPI17 status"
		::= { tly3032c04v1Entry 35 }

		-- 1.3.6.1.4.1.10106.3.101291.1.1.36
		tly3032c04v1Gpi17TrapEnable OBJECT-TYPE
			SYNTAX AlarmEnable
			MAX-ACCESS read-write
			STATUS current
			DESCRIPTION
				"GPI17 status Trap Enable"
		::= { tly3032c04v1Entry 36 }

		-- 1.3.6.1.4.1.10106.3.101291.1.1.37
		tly3032c04v1Gpi18 OBJECT-TYPE
			SYNTAX Bit0Ina1Act
			MAX-ACCESS read-only
			STATUS current
			DESCRIPTION
				"GPI18 status"
		::= { tly3032c04v1Entry 37 }

		-- 1.3.6.1.4.1.10106.3.101291.1.1.38
		tly3032c04v1Gpi18TrapEnable OBJECT-TYPE
			SYNTAX AlarmEnable
			MAX-ACCESS read-write
			STATUS current
			DESCRIPTION
				"GPI18 status Trap Enable"
		::= { tly3032c04v1Entry 38 }

		-- 1.3.6.1.4.1.10106.3.101291.1.1.39
		tly3032c04v1Gpi19 OBJECT-TYPE
			SYNTAX Bit0Ina1Act
			MAX-ACCESS read-only
			STATUS current
			DESCRIPTION
				"GPI19 status"
		::= { tly3032c04v1Entry 39 }

		-- 1.3.6.1.4.1.10106.3.101291.1.1.40
		tly3032c04v1Gpi19TrapEnable OBJECT-TYPE
			SYNTAX AlarmEnable
			MAX-ACCESS read-write
			STATUS current
			DESCRIPTION
				"GPI19 status Trap Enable"
		::= { tly3032c04v1Entry 40 }

		-- 1.3.6.1.4.1.10106.3.101291.1.1.41
		tly3032c04v1Gpi20 OBJECT-TYPE
			SYNTAX Bit0Ina1Act
			MAX-ACCESS read-only
			STATUS current
			DESCRIPTION
				"GPI20 status"
		::= { tly3032c04v1Entry 41 }

		-- 1.3.6.1.4.1.10106.3.101291.1.1.42
		tly3032c04v1Gpi20TrapEnable OBJECT-TYPE
			SYNTAX AlarmEnable
			MAX-ACCESS read-write
			STATUS current
			DESCRIPTION
				"GPI20 status Trap Enable"
		::= { tly3032c04v1Entry 42 }

		-- 1.3.6.1.4.1.10106.3.101291.1.1.43
		tly3032c04v1Gpi21 OBJECT-TYPE
			SYNTAX Bit0Ina1Act
			MAX-ACCESS read-only
			STATUS current
			DESCRIPTION
				"GPI21 status"
		::= { tly3032c04v1Entry 43 }

		-- 1.3.6.1.4.1.10106.3.101291.1.1.44
		tly3032c04v1Gpi21TrapEnable OBJECT-TYPE
			SYNTAX AlarmEnable
			MAX-ACCESS read-write
			STATUS current
			DESCRIPTION
				"GPI21 status Trap Enable"
		::= { tly3032c04v1Entry 44 }

		-- 1.3.6.1.4.1.10106.3.101291.1.1.45
		tly3032c04v1Gpi22 OBJECT-TYPE
			SYNTAX Bit0Ina1Act
			MAX-ACCESS read-only
			STATUS current
			DESCRIPTION
				"GPI22 status"
		::= { tly3032c04v1Entry 45 }

		-- 1.3.6.1.4.1.10106.3.101291.1.1.46
		tly3032c04v1Gpi22TrapEnable OBJECT-TYPE
			SYNTAX AlarmEnable
			MAX-ACCESS read-write
			STATUS current
			DESCRIPTION
				"GPI22 status Trap Enable"
		::= { tly3032c04v1Entry 46 }

		-- 1.3.6.1.4.1.10106.3.101291.1.1.47
		tly3032c04v1Gpi23 OBJECT-TYPE
			SYNTAX Bit0Ina1Act
			MAX-ACCESS read-only
			STATUS current
			DESCRIPTION
				"GPI23 status"
		::= { tly3032c04v1Entry 47 }

		-- 1.3.6.1.4.1.10106.3.101291.1.1.48
		tly3032c04v1Gpi23TrapEnable OBJECT-TYPE
			SYNTAX AlarmEnable
			MAX-ACCESS read-write
			STATUS current
			DESCRIPTION
				"GPI23 status Trap Enable"
		::= { tly3032c04v1Entry 48 }

		-- 1.3.6.1.4.1.10106.3.101291.1.1.49
		tly3032c04v1Gpi24 OBJECT-TYPE
			SYNTAX Bit0Ina1Act
			MAX-ACCESS read-only
			STATUS current
			DESCRIPTION
				"GPI24 status"
		::= { tly3032c04v1Entry 49 }

		-- 1.3.6.1.4.1.10106.3.101291.1.1.50
		tly3032c04v1Gpi24TrapEnable OBJECT-TYPE
			SYNTAX AlarmEnable
			MAX-ACCESS read-write
			STATUS current
			DESCRIPTION
				"GPI24 status Trap Enable"
		::= { tly3032c04v1Entry 50 }

		-- 1.3.6.1.4.1.10106.3.101291.1.1.51
		tly3032c04v1Gpi25 OBJECT-TYPE
			SYNTAX Bit0Ina1Act
			MAX-ACCESS read-only
			STATUS current
			DESCRIPTION
				"GPI25 status"
		::= { tly3032c04v1Entry 51 }

		-- 1.3.6.1.4.1.10106.3.101291.1.1.52
		tly3032c04v1Gpi25TrapEnable OBJECT-TYPE
			SYNTAX AlarmEnable
			MAX-ACCESS read-write
			STATUS current
			DESCRIPTION
				"GPI25 status Trap Enable"
		::= { tly3032c04v1Entry 52 }

		-- 1.3.6.1.4.1.10106.3.101291.1.1.53
		tly3032c04v1Gpi26 OBJECT-TYPE
			SYNTAX Bit0Ina1Act
			MAX-ACCESS read-only
			STATUS current
			DESCRIPTION
				"GPI26 status"
		::= { tly3032c04v1Entry 53 }

		-- 1.3.6.1.4.1.10106.3.101291.1.1.54
		tly3032c04v1Gpi26TrapEnable OBJECT-TYPE
			SYNTAX AlarmEnable
			MAX-ACCESS read-write
			STATUS current
			DESCRIPTION
				"GPI26 status Trap Enable"
		::= { tly3032c04v1Entry 54 }

		-- 1.3.6.1.4.1.10106.3.101291.1.1.55
		tly3032c04v1Gpi27 OBJECT-TYPE
			SYNTAX Bit0Ina1Act
			MAX-ACCESS read-only
			STATUS current
			DESCRIPTION
				"GPI27 status"
		::= { tly3032c04v1Entry 55 }

		-- 1.3.6.1.4.1.10106.3.101291.1.1.56
		tly3032c04v1Gpi27TrapEnable OBJECT-TYPE
			SYNTAX AlarmEnable
			MAX-ACCESS read-write
			STATUS current
			DESCRIPTION
				"GPI27 status Trap Enable"
		::= { tly3032c04v1Entry 56 }

		-- 1.3.6.1.4.1.10106.3.101291.1.1.57
		tly3032c04v1Gpi28 OBJECT-TYPE
			SYNTAX Bit0Ina1Act
			MAX-ACCESS read-only
			STATUS current
			DESCRIPTION
				"GPI28 status"
		::= { tly3032c04v1Entry 57 }

		-- 1.3.6.1.4.1.10106.3.101291.1.1.58
		tly3032c04v1Gpi28TrapEnable OBJECT-TYPE
			SYNTAX AlarmEnable
			MAX-ACCESS read-write
			STATUS current
			DESCRIPTION
				"GPI28 status Trap Enable"
		::= { tly3032c04v1Entry 58 }

		-- 1.3.6.1.4.1.10106.3.101291.1.1.59
		tly3032c04v1Gpi29 OBJECT-TYPE
			SYNTAX Bit0Ina1Act
			MAX-ACCESS read-only
			STATUS current
			DESCRIPTION
				"GPI29 status"
		::= { tly3032c04v1Entry 59 }

		-- 1.3.6.1.4.1.10106.3.101291.1.1.60
		tly3032c04v1Gpi29TrapEnable OBJECT-TYPE
			SYNTAX AlarmEnable
			MAX-ACCESS read-write
			STATUS current
			DESCRIPTION
				"GPI29 status Trap Enable"
		::= { tly3032c04v1Entry 60 }

		-- 1.3.6.1.4.1.10106.3.101291.1.1.61
		tly3032c04v1Gpi30 OBJECT-TYPE
			SYNTAX Bit0Ina1Act
			MAX-ACCESS read-only
			STATUS current
			DESCRIPTION
				"GPI30 status"
		::= { tly3032c04v1Entry 61 }

		-- 1.3.6.1.4.1.10106.3.101291.1.1.62
		tly3032c04v1Gpi30TrapEnable OBJECT-TYPE
			SYNTAX AlarmEnable
			MAX-ACCESS read-write
			STATUS current
			DESCRIPTION
				"GPI30 status Trap Enable"
		::= { tly3032c04v1Entry 62 }

		-- 1.3.6.1.4.1.10106.3.101291.1.1.63
		tly3032c04v1Gpi31 OBJECT-TYPE
			SYNTAX Bit0Ina1Act
			MAX-ACCESS read-only
			STATUS current
			DESCRIPTION
				"GPI31 status"
		::= { tly3032c04v1Entry 63 }

		-- 1.3.6.1.4.1.10106.3.101291.1.1.64
		tly3032c04v1Gpi31TrapEnable OBJECT-TYPE
			SYNTAX AlarmEnable
			MAX-ACCESS read-write
			STATUS current
			DESCRIPTION
				"GPI31 status Trap Enable"
		::= { tly3032c04v1Entry 64 }

		-- 1.3.6.1.4.1.10106.3.101291.1.1.65
		tly3032c04v1Gpi32 OBJECT-TYPE
			SYNTAX Bit0Ina1Act
			MAX-ACCESS read-only
			STATUS current
			DESCRIPTION
				"GPI32 status"
		::= { tly3032c04v1Entry 65 }

		-- 1.3.6.1.4.1.10106.3.101291.1.1.66
		tly3032c04v1Gpi32TrapEnable OBJECT-TYPE
			SYNTAX AlarmEnable
			MAX-ACCESS read-write
			STATUS current
			DESCRIPTION
				"GPI32 status Trap Enable"
		::= { tly3032c04v1Entry 66 }

		-- 1.3.6.1.4.1.10106.3.478901
		tle0001c02v1 OBJECT IDENTIFIER ::= { albalaProducts 478901 }

		-- 1.3.6.1.4.1.10106.3.478901.1
		tle0001c02v1Table  OBJECT-TYPE
			SYNTAX SEQUENCE OF Tle0001c02v1Entry
			MAX-ACCESS not-accessible
			STATUS current
			DESCRIPTION
				"Module  TLE0001C02V1 Table"
			::= { tle0001c02v1 1 }

		-- 1.3.6.1.4.1.10106.3.478901.1.1
		tle0001c02v1Entry  OBJECT-TYPE
			SYNTAX Tle0001c02v1Entry
			MAX-ACCESS not-accessible
			STATUS current
			DESCRIPTION
				"Module TLE0001C02V1 Entry"
			INDEX { tle0001c02v1Index }
			::= { tle0001c02v1Table 1 }

			Tle0001c02v1Entry ::=
			SEQUENCE {
				tle0001c02v1Index
				ModuleIndex,
				tle0001c02v1SerialNo
				SerialNo,
				tle0001c02v1App1Ena
				Bit0No1Yes,
				tle0001c02v1App1EnaTrapEnable
				AlarmEnable,
				tle0001c02v1App2Ena
				Bit0No1Yes,
				tle0001c02v1App3Ena
				Bit0No1Yes
			 }

		-- 1.3.6.1.4.1.10106.3.101291.1.1.1
		tle0001c02v1Index OBJECT-TYPE
			SYNTAX ModuleIndex
			MAX-ACCESS read-only
			STATUS current
			DESCRIPTION
				"Index of TLE0001C02V1 Table"
		::= { tle0001c02v1Entry 1 }

		-- 1.3.6.1.4.1.10106.3.101291.1.1.3
		tle0001c02v1SerialNo OBJECT-TYPE
			SYNTAX SerialNo
			MAX-ACCESS read-only
			STATUS current
			DESCRIPTION
				"Serial number"
		::= { tle0001c02v1Entry 3 }

		-- 1.3.6.1.4.1.10106.3.101291.1.1.5
		tle0001c02v1App1Ena OBJECT-TYPE
			SYNTAX Bit0No1Yes
			MAX-ACCESS read-only
			STATUS current
			DESCRIPTION
				"Indicates the event log is enabled"
		::= { tle0001c02v1Entry 5 }

		-- 1.3.6.1.4.1.10106.3.101291.1.1.6
		tle0001c02v1App1EnaTrapEnable OBJECT-TYPE
			SYNTAX AlarmEnable
			MAX-ACCESS read-write
			STATUS current
			DESCRIPTION
				"Indicates the event log is enabled Trap Enable"
		::= { tle0001c02v1Entry 6 }

		-- 1.3.6.1.4.1.10106.3.101291.1.1.7
		tle0001c02v1App2Ena OBJECT-TYPE
			SYNTAX Bit0No1Yes
			MAX-ACCESS read-only
			STATUS current
			DESCRIPTION
				"Indicates the SNMP is enabled"
		::= { tle0001c02v1Entry 7 }

		-- 1.3.6.1.4.1.10106.3.101291.1.1.9
		tle0001c02v1App3Ena OBJECT-TYPE
			SYNTAX Bit0No1Yes
			MAX-ACCESS read-only
			STATUS current
			DESCRIPTION
				"Indicates the access control is enabled"
		::= { tle0001c02v1Entry 9 }

		-- 1.3.6.1.4.1.10106.3.483501
		udp2000c01v1 OBJECT IDENTIFIER ::= { albalaProducts 483501 }

		-- 1.3.6.1.4.1.10106.3.483501.1
		udp2000c01v1Table  OBJECT-TYPE
			SYNTAX SEQUENCE OF Udp2000c01v1Entry
			MAX-ACCESS not-accessible
			STATUS current
			DESCRIPTION
				"Module  UDP2000C01V1 Table"
			::= { udp2000c01v1 1 }

		-- 1.3.6.1.4.1.10106.3.483501.1.1
		udp2000c01v1Entry  OBJECT-TYPE
			SYNTAX Udp2000c01v1Entry
			MAX-ACCESS not-accessible
			STATUS current
			DESCRIPTION
				"Module UDP2000C01V1 Entry"
			INDEX { udp2000c01v1Index }
			::= { udp2000c01v1Table 1 }

			Udp2000c01v1Entry ::=
			SEQUENCE {
				udp2000c01v1Index
				ModuleIndex,
				udp2000c01v1ActivePreset
				Preset16Active,
				udp2000c01v1LoadPreset
				Preset16Load,
				udp2000c01v1SavePreset
				Preset16Save,
				udp2000c01v1EthMode2
				EthMode2000,
				udp2000c01v1SpeedForce2
				Bit0Ann1For,
				udp2000c01v1TxtInsEn
				BitMask,
				udp2000c01v1TxtExtEn
				BitMask,
				udp2000c01v1TimeCodeInsEn
				BitMask,
				udp2000c01v1VideoCleanEn
				BitMask,
				udp2000c01v1VidFreeRunEn
				BitMask,
				udp2000c01v1PingEnable
				Bit0No1Yes,
				udp2000c01v1LocalIpAdd3
				Uint8,
				udp2000c01v1LocalIpAdd2
				Uint8,
				udp2000c01v1LocalIpAdd1
				Uint8,
				udp2000c01v1LocalIpAdd0
				Uint8,
				udp2000c01v1DstPortMsb
				Uint8,
				udp2000c01v1DstPortLsb
				Uint8,
				udp2000c01v1TxUipAdd3
				Uint8,
				udp2000c01v1TxUipAdd2
				Uint8,
				udp2000c01v1TxUipAdd1
				Uint8,
				udp2000c01v1TxUipAdd0
				Uint8,
				udp2000c01v1TxDPortMsb
				Uint8,
				udp2000c01v1TxDPortLsb
				Uint8,
				udp2000c01v1LocalIpGway3
				Uint8,
				udp2000c01v1LocalIpGway2
				Uint8,
				udp2000c01v1LocalIpGway1
				Uint8,
				udp2000c01v1LocalIpGway0
				Uint8,
				udp2000c01v1LocalIpMask3
				Uint8,
				udp2000c01v1LocalIpMask2
				Uint8,
				udp2000c01v1LocalIpMask1
				Uint8,
				udp2000c01v1LocalIpMask0
				Uint8,
				udp2000c01v1NoSignal
				BitFail,
				udp2000c01v1NoSignalTrapEnable
				AlarmEnable,
				udp2000c01v1Unlock
				BitFail,
				udp2000c01v1UnlockTrapEnable
				AlarmEnable,
				udp2000c01v1EdhError
				BitFail,
				udp2000c01v1FormatB
				SdiHd3gFmt3,
				udp2000c01v1DestAvailable
				Bit0No1Yes,
				udp2000c01v1DestAvailableTrapEnable
				AlarmEnable,
				udp2000c01v1PingStatus
				IpaPingStat,
				udp2000c01v1PingStatusTrapEnable
				AlarmEnable,
				udp2000c01v1EmbedderFail
				BitFail,
				udp2000c01v1EmbedderFailTrapEnable
				AlarmEnable,
				udp2000c01v1DeembedderFail
				BitFail,
				udp2000c01v1DeembedderFailTrapEnable
				AlarmEnable,
				udp2000c01v1EmbedderValid
				BitFailN,
				udp2000c01v1EmbedderValidTrapEnable
				AlarmEnable,
				udp2000c01v1DeembedderValid
				BitFailN,
				udp2000c01v1DeembedderValidTrapEnable
				AlarmEnable,
				udp2000c01v1Link2
				Ipa2EtherStat,
				udp2000c01v1System2
				Ipa2EtherSys,
				udp2000c01v1VitcAtcPres
				BitFailN,
				udp2000c01v1VitcAtcPresTrapEnable
				AlarmEnable,
				udp2000c01v1SerialNo
				SerialNo
			 }

		-- 1.3.6.1.4.1.10106.3.101291.1.1.1
		udp2000c01v1Index OBJECT-TYPE
			SYNTAX ModuleIndex
			MAX-ACCESS read-only
			STATUS current
			DESCRIPTION
				"Index of UDP2000C01V1 Table"
		::= { udp2000c01v1Entry 1 }

		-- 1.3.6.1.4.1.10106.3.101291.1.1.3
		udp2000c01v1ActivePreset OBJECT-TYPE
			SYNTAX Preset16Active
			MAX-ACCESS read-only
			STATUS current
			DESCRIPTION
				"Shows the active preset"
		::= { udp2000c01v1Entry 3 }

		-- 1.3.6.1.4.1.10106.3.101291.1.1.5
		udp2000c01v1LoadPreset OBJECT-TYPE
			SYNTAX Preset16Load
			MAX-ACCESS read-write
			STATUS current
			DESCRIPTION
				"Allows loading a preset"
		::= { udp2000c01v1Entry 5 }

		-- 1.3.6.1.4.1.10106.3.101291.1.1.7
		udp2000c01v1SavePreset OBJECT-TYPE
			SYNTAX Preset16Save
			MAX-ACCESS read-write
			STATUS current
			DESCRIPTION
				"Allows saving a preset"
		::= { udp2000c01v1Entry 7 }

		-- 1.3.6.1.4.1.10106.3.101291.1.1.9
		udp2000c01v1EthMode2 OBJECT-TYPE
			SYNTAX EthMode2000
			MAX-ACCESS read-write
			STATUS current
			DESCRIPTION
				"Allows selecting the Ethernet operating mode"
		::= { udp2000c01v1Entry 9 }

		-- 1.3.6.1.4.1.10106.3.101291.1.1.11
		udp2000c01v1SpeedForce2 OBJECT-TYPE
			SYNTAX Bit0Ann1For
			MAX-ACCESS read-write
			STATUS current
			DESCRIPTION
				"Allows selecting if the speed/mode is forced or announced for autonegotiation"
		::= { udp2000c01v1Entry 11 }

		-- 1.3.6.1.4.1.10106.3.101291.1.1.13
		udp2000c01v1TxtInsEn OBJECT-TYPE
			SYNTAX BitMask
			MAX-ACCESS read-write
			STATUS current
			DESCRIPTION
				"Enables insertion of UDP packets over TXT"
		::= { udp2000c01v1Entry 13 }

		-- 1.3.6.1.4.1.10106.3.101291.1.1.15
		udp2000c01v1TxtExtEn OBJECT-TYPE
			SYNTAX BitMask
			MAX-ACCESS read-write
			STATUS current
			DESCRIPTION
				"Enables UDP packets extraction"
		::= { udp2000c01v1Entry 15 }

		-- 1.3.6.1.4.1.10106.3.101291.1.1.17
		udp2000c01v1TimeCodeInsEn OBJECT-TYPE
			SYNTAX BitMask
			MAX-ACCESS read-write
			STATUS current
			DESCRIPTION
				"Enables time code insertion"
		::= { udp2000c01v1Entry 17 }

		-- 1.3.6.1.4.1.10106.3.101291.1.1.19
		udp2000c01v1VideoCleanEn OBJECT-TYPE
			SYNTAX BitMask
			MAX-ACCESS read-write
			STATUS current
			DESCRIPTION
				"Enables video cleaning of lines where txt has been detected"
		::= { udp2000c01v1Entry 19 }

		-- 1.3.6.1.4.1.10106.3.101291.1.1.21
		udp2000c01v1VidFreeRunEn OBJECT-TYPE
			SYNTAX BitMask
			MAX-ACCESS read-write
			STATUS current
			DESCRIPTION
				"Enables frre run video generator"
		::= { udp2000c01v1Entry 21 }

		-- 1.3.6.1.4.1.10106.3.101291.1.1.23
		udp2000c01v1PingEnable OBJECT-TYPE
			SYNTAX Bit0No1Yes
			MAX-ACCESS read-write
			STATUS current
			DESCRIPTION
				"Allows making a periodic ping to the unicast address"
		::= { udp2000c01v1Entry 23 }

		-- 1.3.6.1.4.1.10106.3.101291.1.1.25
		udp2000c01v1LocalIpAdd3 OBJECT-TYPE
			SYNTAX Uint8
			MAX-ACCESS read-write
			STATUS current
			DESCRIPTION
				"IP address (3)"
		::= { udp2000c01v1Entry 25 }

		-- 1.3.6.1.4.1.10106.3.101291.1.1.27
		udp2000c01v1LocalIpAdd2 OBJECT-TYPE
			SYNTAX Uint8
			MAX-ACCESS read-write
			STATUS current
			DESCRIPTION
				"IP address (2)"
		::= { udp2000c01v1Entry 27 }

		-- 1.3.6.1.4.1.10106.3.101291.1.1.29
		udp2000c01v1LocalIpAdd1 OBJECT-TYPE
			SYNTAX Uint8
			MAX-ACCESS read-write
			STATUS current
			DESCRIPTION
				"IP address (1)"
		::= { udp2000c01v1Entry 29 }

		-- 1.3.6.1.4.1.10106.3.101291.1.1.31
		udp2000c01v1LocalIpAdd0 OBJECT-TYPE
			SYNTAX Uint8
			MAX-ACCESS read-write
			STATUS current
			DESCRIPTION
				"IP address (0)"
		::= { udp2000c01v1Entry 31 }

		-- 1.3.6.1.4.1.10106.3.101291.1.1.33
		udp2000c01v1DstPortMsb OBJECT-TYPE
			SYNTAX Uint8
			MAX-ACCESS read-write
			STATUS current
			DESCRIPTION
				"Destination port (msb)"
		::= { udp2000c01v1Entry 33 }

		-- 1.3.6.1.4.1.10106.3.101291.1.1.35
		udp2000c01v1DstPortLsb OBJECT-TYPE
			SYNTAX Uint8
			MAX-ACCESS read-write
			STATUS current
			DESCRIPTION
				"Destination port (lsb)"
		::= { udp2000c01v1Entry 35 }

		-- 1.3.6.1.4.1.10106.3.101291.1.1.37
		udp2000c01v1TxUipAdd3 OBJECT-TYPE
			SYNTAX Uint8
			MAX-ACCESS read-write
			STATUS current
			DESCRIPTION
				"Destination IP address (3)"
		::= { udp2000c01v1Entry 37 }

		-- 1.3.6.1.4.1.10106.3.101291.1.1.39
		udp2000c01v1TxUipAdd2 OBJECT-TYPE
			SYNTAX Uint8
			MAX-ACCESS read-write
			STATUS current
			DESCRIPTION
				"Destination IP address (2)"
		::= { udp2000c01v1Entry 39 }

		-- 1.3.6.1.4.1.10106.3.101291.1.1.41
		udp2000c01v1TxUipAdd1 OBJECT-TYPE
			SYNTAX Uint8
			MAX-ACCESS read-write
			STATUS current
			DESCRIPTION
				"Destination IP address (1)"
		::= { udp2000c01v1Entry 41 }

		-- 1.3.6.1.4.1.10106.3.101291.1.1.43
		udp2000c01v1TxUipAdd0 OBJECT-TYPE
			SYNTAX Uint8
			MAX-ACCESS read-write
			STATUS current
			DESCRIPTION
				"Destination IP address (0)"
		::= { udp2000c01v1Entry 43 }

		-- 1.3.6.1.4.1.10106.3.101291.1.1.45
		udp2000c01v1TxDPortMsb OBJECT-TYPE
			SYNTAX Uint8
			MAX-ACCESS read-write
			STATUS current
			DESCRIPTION
				"Destination port (msb)"
		::= { udp2000c01v1Entry 45 }

		-- 1.3.6.1.4.1.10106.3.101291.1.1.47
		udp2000c01v1TxDPortLsb OBJECT-TYPE
			SYNTAX Uint8
			MAX-ACCESS read-write
			STATUS current
			DESCRIPTION
				"Destination port (lsb)"
		::= { udp2000c01v1Entry 47 }

		-- 1.3.6.1.4.1.10106.3.101291.1.1.49
		udp2000c01v1LocalIpGway3 OBJECT-TYPE
			SYNTAX Uint8
			MAX-ACCESS read-write
			STATUS current
			DESCRIPTION
				"Gateway IP address (3)"
		::= { udp2000c01v1Entry 49 }

		-- 1.3.6.1.4.1.10106.3.101291.1.1.51
		udp2000c01v1LocalIpGway2 OBJECT-TYPE
			SYNTAX Uint8
			MAX-ACCESS read-write
			STATUS current
			DESCRIPTION
				"Gateway IP address (2)"
		::= { udp2000c01v1Entry 51 }

		-- 1.3.6.1.4.1.10106.3.101291.1.1.53
		udp2000c01v1LocalIpGway1 OBJECT-TYPE
			SYNTAX Uint8
			MAX-ACCESS read-write
			STATUS current
			DESCRIPTION
				"Gateway IP address (1)"
		::= { udp2000c01v1Entry 53 }

		-- 1.3.6.1.4.1.10106.3.101291.1.1.55
		udp2000c01v1LocalIpGway0 OBJECT-TYPE
			SYNTAX Uint8
			MAX-ACCESS read-write
			STATUS current
			DESCRIPTION
				"Gateway IP address (0)"
		::= { udp2000c01v1Entry 55 }

		-- 1.3.6.1.4.1.10106.3.101291.1.1.57
		udp2000c01v1LocalIpMask3 OBJECT-TYPE
			SYNTAX Uint8
			MAX-ACCESS read-write
			STATUS current
			DESCRIPTION
				"IP mask (3)"
		::= { udp2000c01v1Entry 57 }

		-- 1.3.6.1.4.1.10106.3.101291.1.1.59
		udp2000c01v1LocalIpMask2 OBJECT-TYPE
			SYNTAX Uint8
			MAX-ACCESS read-write
			STATUS current
			DESCRIPTION
				"IP mask (2)"
		::= { udp2000c01v1Entry 59 }

		-- 1.3.6.1.4.1.10106.3.101291.1.1.61
		udp2000c01v1LocalIpMask1 OBJECT-TYPE
			SYNTAX Uint8
			MAX-ACCESS read-write
			STATUS current
			DESCRIPTION
				"IP mask (1)"
		::= { udp2000c01v1Entry 61 }

		-- 1.3.6.1.4.1.10106.3.101291.1.1.63
		udp2000c01v1LocalIpMask0 OBJECT-TYPE
			SYNTAX Uint8
			MAX-ACCESS read-write
			STATUS current
			DESCRIPTION
				"IP mask (0)"
		::= { udp2000c01v1Entry 63 }

		-- 1.3.6.1.4.1.10106.3.101291.1.1.65
		udp2000c01v1NoSignal OBJECT-TYPE
			SYNTAX BitFail
			MAX-ACCESS read-only
			STATUS current
			DESCRIPTION
				"There is no SDI signal or the format is not supported"
		::= { udp2000c01v1Entry 65 }

		-- 1.3.6.1.4.1.10106.3.101291.1.1.66
		udp2000c01v1NoSignalTrapEnable OBJECT-TYPE
			SYNTAX AlarmEnable
			MAX-ACCESS read-write
			STATUS current
			DESCRIPTION
				"There is no SDI signal or the format is not supported Trap Enable"
		::= { udp2000c01v1Entry 66 }

		-- 1.3.6.1.4.1.10106.3.101291.1.1.67
		udp2000c01v1Unlock OBJECT-TYPE
			SYNTAX BitFail
			MAX-ACCESS read-only
			STATUS current
			DESCRIPTION
				"Indicates signal unlock fail"
		::= { udp2000c01v1Entry 67 }

		-- 1.3.6.1.4.1.10106.3.101291.1.1.68
		udp2000c01v1UnlockTrapEnable OBJECT-TYPE
			SYNTAX AlarmEnable
			MAX-ACCESS read-write
			STATUS current
			DESCRIPTION
				"Indicates signal unlock fail Trap Enable"
		::= { udp2000c01v1Entry 68 }

		-- 1.3.6.1.4.1.10106.3.101291.1.1.69
		udp2000c01v1EdhError OBJECT-TYPE
			SYNTAX BitFail
			MAX-ACCESS read-only
			STATUS current
			DESCRIPTION
				"There are EDH/CRC errors on SDI signal"
		::= { udp2000c01v1Entry 69 }

		-- 1.3.6.1.4.1.10106.3.101291.1.1.71
		udp2000c01v1FormatB OBJECT-TYPE
			SYNTAX SdiHd3gFmt3
			MAX-ACCESS read-only
			STATUS current
			DESCRIPTION
				"Indicates the SDI received signal format"
		::= { udp2000c01v1Entry 71 }

		-- 1.3.6.1.4.1.10106.3.101291.1.1.73
		udp2000c01v1DestAvailable OBJECT-TYPE
			SYNTAX Bit0No1Yes
			MAX-ACCESS read-only
			STATUS current
			DESCRIPTION
				"Destination IP available"
		::= { udp2000c01v1Entry 73 }

		-- 1.3.6.1.4.1.10106.3.101291.1.1.74
		udp2000c01v1DestAvailableTrapEnable OBJECT-TYPE
			SYNTAX AlarmEnable
			MAX-ACCESS read-write
			STATUS current
			DESCRIPTION
				"Destination IP available Trap Enable"
		::= { udp2000c01v1Entry 74 }

		-- 1.3.6.1.4.1.10106.3.101291.1.1.75
		udp2000c01v1PingStatus OBJECT-TYPE
			SYNTAX IpaPingStat
			MAX-ACCESS read-only
			STATUS current
			DESCRIPTION
				"Ping status"
		::= { udp2000c01v1Entry 75 }

		-- 1.3.6.1.4.1.10106.3.101291.1.1.76
		udp2000c01v1PingStatusTrapEnable OBJECT-TYPE
			SYNTAX AlarmEnable
			MAX-ACCESS read-write
			STATUS current
			DESCRIPTION
				"Ping status Trap Enable"
		::= { udp2000c01v1Entry 76 }

		-- 1.3.6.1.4.1.10106.3.101291.1.1.77
		udp2000c01v1EmbedderFail OBJECT-TYPE
			SYNTAX BitFail
			MAX-ACCESS read-only
			STATUS current
			DESCRIPTION
				"Embedder fail"
		::= { udp2000c01v1Entry 77 }

		-- 1.3.6.1.4.1.10106.3.101291.1.1.78
		udp2000c01v1EmbedderFailTrapEnable OBJECT-TYPE
			SYNTAX AlarmEnable
			MAX-ACCESS read-write
			STATUS current
			DESCRIPTION
				"Embedder fail Trap Enable"
		::= { udp2000c01v1Entry 78 }

		-- 1.3.6.1.4.1.10106.3.101291.1.1.79
		udp2000c01v1DeembedderFail OBJECT-TYPE
			SYNTAX BitFail
			MAX-ACCESS read-only
			STATUS current
			DESCRIPTION
				"Deembedder fail"
		::= { udp2000c01v1Entry 79 }

		-- 1.3.6.1.4.1.10106.3.101291.1.1.80
		udp2000c01v1DeembedderFailTrapEnable OBJECT-TYPE
			SYNTAX AlarmEnable
			MAX-ACCESS read-write
			STATUS current
			DESCRIPTION
				"Deembedder fail Trap Enable"
		::= { udp2000c01v1Entry 80 }

		-- 1.3.6.1.4.1.10106.3.101291.1.1.81
		udp2000c01v1EmbedderValid OBJECT-TYPE
			SYNTAX BitFailN
			MAX-ACCESS read-only
			STATUS current
			DESCRIPTION
				"Embedder RX valid"
		::= { udp2000c01v1Entry 81 }

		-- 1.3.6.1.4.1.10106.3.101291.1.1.82
		udp2000c01v1EmbedderValidTrapEnable OBJECT-TYPE
			SYNTAX AlarmEnable
			MAX-ACCESS read-write
			STATUS current
			DESCRIPTION
				"Embedder RX valid Trap Enable"
		::= { udp2000c01v1Entry 82 }

		-- 1.3.6.1.4.1.10106.3.101291.1.1.83
		udp2000c01v1DeembedderValid OBJECT-TYPE
			SYNTAX BitFailN
			MAX-ACCESS read-only
			STATUS current
			DESCRIPTION
				"Deembedder RX valid"
		::= { udp2000c01v1Entry 83 }

		-- 1.3.6.1.4.1.10106.3.101291.1.1.84
		udp2000c01v1DeembedderValidTrapEnable OBJECT-TYPE
			SYNTAX AlarmEnable
			MAX-ACCESS read-write
			STATUS current
			DESCRIPTION
				"Deembedder RX valid Trap Enable"
		::= { udp2000c01v1Entry 84 }

		-- 1.3.6.1.4.1.10106.3.101291.1.1.85
		udp2000c01v1Link2 OBJECT-TYPE
			SYNTAX Ipa2EtherStat
			MAX-ACCESS read-only
			STATUS current
			DESCRIPTION
				"Ethernet conection status"
		::= { udp2000c01v1Entry 85 }

		-- 1.3.6.1.4.1.10106.3.101291.1.1.87
		udp2000c01v1System2 OBJECT-TYPE
			SYNTAX Ipa2EtherSys
			MAX-ACCESS read-only
			STATUS current
			DESCRIPTION
				"Ethernet conection system"
		::= { udp2000c01v1Entry 87 }

		-- 1.3.6.1.4.1.10106.3.101291.1.1.89
		udp2000c01v1VitcAtcPres OBJECT-TYPE
			SYNTAX BitFailN
			MAX-ACCESS read-only
			STATUS current
			DESCRIPTION
				"Input VITC-ATC presence"
		::= { udp2000c01v1Entry 89 }

		-- 1.3.6.1.4.1.10106.3.101291.1.1.90
		udp2000c01v1VitcAtcPresTrapEnable OBJECT-TYPE
			SYNTAX AlarmEnable
			MAX-ACCESS read-write
			STATUS current
			DESCRIPTION
				"Input VITC-ATC presence Trap Enable"
		::= { udp2000c01v1Entry 90 }

		-- 1.3.6.1.4.1.10106.3.101291.1.1.91
		udp2000c01v1SerialNo OBJECT-TYPE
			SYNTAX SerialNo
			MAX-ACCESS read-only
			STATUS current
			DESCRIPTION
				"Serial number"
		::= { udp2000c01v1Entry 91 }

		-- 1.3.6.1.4.1.10106.3.484901
		aem2008c01v1 OBJECT IDENTIFIER ::= { albalaProducts 484901 }

		-- 1.3.6.1.4.1.10106.3.484901.1
		aem2008c01v1Table  OBJECT-TYPE
			SYNTAX SEQUENCE OF Aem2008c01v1Entry
			MAX-ACCESS not-accessible
			STATUS current
			DESCRIPTION
				"Module  AEM2008C01V1 Table"
			::= { aem2008c01v1 1 }

		-- 1.3.6.1.4.1.10106.3.484901.1.1
		aem2008c01v1Entry  OBJECT-TYPE
			SYNTAX Aem2008c01v1Entry
			MAX-ACCESS not-accessible
			STATUS current
			DESCRIPTION
				"Module AEM2008C01V1 Entry"
			INDEX { aem2008c01v1Index }
			::= { aem2008c01v1Table 1 }

			Aem2008c01v1Entry ::=
			SEQUENCE {
				aem2008c01v1Index
				ModuleIndex,
				aem2008c01v1Section
				AudioChannels,
				aem2008c01v1FrqSamp
				Bit0481192,
				aem2008c01v1CleanH
				BitMask,
				aem2008c01v1CoarseGain
				LevelDbX6,
				aem2008c01v1SdiInFail
				BitFail,
				aem2008c01v1SdiInFailTrapEnable
				AlarmEnable,
				aem2008c01v1EdhInFail
				BitFail,
				aem2008c01v1EdhInFailTrapEnable
				AlarmEnable,
				aem2008c01v1AudFail
				BitFail,
				aem2008c01v1AudFailTrapEnable
				AlarmEnable,
				aem2008c01v1AudClip
				BitFail,
				aem2008c01v1AudClipTrapEnable
				AlarmEnable,
				aem2008c01v1Fmt
				Bit05251625,
				aem2008c01v1G1Pres
				Bit0No1Yes,
				aem2008c01v1G2Pres
				Bit0No1Yes,
				aem2008c01v1G3Pres
				Bit0No1Yes,
				aem2008c01v1G4Pres
				Bit0No1Yes,
				aem2008c01v1Mpx1Pres
				Bit0No1Yes,
				aem2008c01v1Mpx2Pres
				Bit0No1Yes,
				aem2008c01v1Mpx3Pres
				Bit0No1Yes,
				aem2008c01v1Mpx4Pres
				Bit0No1Yes,
				aem2008c01v1SerialNo
				SerialNo,
				aem2008c01v1Invert
				Bit0Yes1No,
				aem2008c01v1Ref27mFail
				BitFail
			 }

		-- 1.3.6.1.4.1.10106.3.101291.1.1.1
		aem2008c01v1Index OBJECT-TYPE
			SYNTAX ModuleIndex
			MAX-ACCESS read-only
			STATUS current
			DESCRIPTION
				"Index of AEM2008C01V1 Table"
		::= { aem2008c01v1Entry 1 }

		-- 1.3.6.1.4.1.10106.3.101291.1.1.3
		aem2008c01v1Section OBJECT-TYPE
			SYNTAX AudioChannels
			MAX-ACCESS read-write
			STATUS current
			DESCRIPTION
				"It selects the channels that will be embedded"
		::= { aem2008c01v1Entry 3 }

		-- 1.3.6.1.4.1.10106.3.101291.1.1.5
		aem2008c01v1FrqSamp OBJECT-TYPE
			SYNTAX Bit0481192
			MAX-ACCESS read-write
			STATUS current
			DESCRIPTION
				"It selects the sampling frequency of the analogue sampling"
		::= { aem2008c01v1Entry 5 }

		-- 1.3.6.1.4.1.10106.3.101291.1.1.7
		aem2008c01v1CleanH OBJECT-TYPE
			SYNTAX BitMask
			MAX-ACCESS read-write
			STATUS current
			DESCRIPTION
				"It enables removing the ancillary packets in the horizontal blanking"
		::= { aem2008c01v1Entry 7 }

		-- 1.3.6.1.4.1.10106.3.101291.1.1.9
		aem2008c01v1CoarseGain OBJECT-TYPE
			SYNTAX LevelDbX6
			MAX-ACCESS read-write
			STATUS current
			DESCRIPTION
				"It selects the gain to apply to the analogue output"
		::= { aem2008c01v1Entry 9 }

		-- 1.3.6.1.4.1.10106.3.101291.1.1.11
		aem2008c01v1SdiInFail OBJECT-TYPE
			SYNTAX BitFail
			MAX-ACCESS read-only
			STATUS current
			DESCRIPTION
				"SDI input signal status"
		::= { aem2008c01v1Entry 11 }

		-- 1.3.6.1.4.1.10106.3.101291.1.1.12
		aem2008c01v1SdiInFailTrapEnable OBJECT-TYPE
			SYNTAX AlarmEnable
			MAX-ACCESS read-write
			STATUS current
			DESCRIPTION
				"SDI input signal status Trap Enable"
		::= { aem2008c01v1Entry 12 }

		-- 1.3.6.1.4.1.10106.3.101291.1.1.13
		aem2008c01v1EdhInFail OBJECT-TYPE
			SYNTAX BitFail
			MAX-ACCESS read-only
			STATUS current
			DESCRIPTION
				"It indicates EDH errors"
		::= { aem2008c01v1Entry 13 }

		-- 1.3.6.1.4.1.10106.3.101291.1.1.14
		aem2008c01v1EdhInFailTrapEnable OBJECT-TYPE
			SYNTAX AlarmEnable
			MAX-ACCESS read-write
			STATUS current
			DESCRIPTION
				"It indicates EDH errors Trap Enable"
		::= { aem2008c01v1Entry 14 }

		-- 1.3.6.1.4.1.10106.3.101291.1.1.15
		aem2008c01v1AudFail OBJECT-TYPE
			SYNTAX BitFail
			MAX-ACCESS read-only
			STATUS current
			DESCRIPTION
				"It indicates there are audio errors"
		::= { aem2008c01v1Entry 15 }

		-- 1.3.6.1.4.1.10106.3.101291.1.1.16
		aem2008c01v1AudFailTrapEnable OBJECT-TYPE
			SYNTAX AlarmEnable
			MAX-ACCESS read-write
			STATUS current
			DESCRIPTION
				"It indicates there are audio errors Trap Enable"
		::= { aem2008c01v1Entry 16 }

		-- 1.3.6.1.4.1.10106.3.101291.1.1.17
		aem2008c01v1AudClip OBJECT-TYPE
			SYNTAX BitFail
			MAX-ACCESS read-only
			STATUS current
			DESCRIPTION
				"It indicates there is analogue clipping at the analogue inputs or digital clipping due to applied gain"
		::= { aem2008c01v1Entry 17 }

		-- 1.3.6.1.4.1.10106.3.101291.1.1.18
		aem2008c01v1AudClipTrapEnable OBJECT-TYPE
			SYNTAX AlarmEnable
			MAX-ACCESS read-write
			STATUS current
			DESCRIPTION
				"It indicates there is analogue clipping at the analogue inputs or digital clipping due to applied gain Trap Enable"
		::= { aem2008c01v1Entry 18 }

		-- 1.3.6.1.4.1.10106.3.101291.1.1.19
		aem2008c01v1Fmt OBJECT-TYPE
			SYNTAX Bit05251625
			MAX-ACCESS read-only
			STATUS current
			DESCRIPTION
				"It indicates the SDI format"
		::= { aem2008c01v1Entry 19 }

		-- 1.3.6.1.4.1.10106.3.101291.1.1.21
		aem2008c01v1G1Pres OBJECT-TYPE
			SYNTAX Bit0No1Yes
			MAX-ACCESS read-only
			STATUS current
			DESCRIPTION
				"It indicates the presence of packets of audio group 1"
		::= { aem2008c01v1Entry 21 }

		-- 1.3.6.1.4.1.10106.3.101291.1.1.23
		aem2008c01v1G2Pres OBJECT-TYPE
			SYNTAX Bit0No1Yes
			MAX-ACCESS read-only
			STATUS current
			DESCRIPTION
				"It indicates the presence of packets of audio group 2"
		::= { aem2008c01v1Entry 23 }

		-- 1.3.6.1.4.1.10106.3.101291.1.1.25
		aem2008c01v1G3Pres OBJECT-TYPE
			SYNTAX Bit0No1Yes
			MAX-ACCESS read-only
			STATUS current
			DESCRIPTION
				"It indicates the presence of packets of audio group 3"
		::= { aem2008c01v1Entry 25 }

		-- 1.3.6.1.4.1.10106.3.101291.1.1.27
		aem2008c01v1G4Pres OBJECT-TYPE
			SYNTAX Bit0No1Yes
			MAX-ACCESS read-only
			STATUS current
			DESCRIPTION
				"It indicates the presence of packets of audio group 4"
		::= { aem2008c01v1Entry 27 }

		-- 1.3.6.1.4.1.10106.3.101291.1.1.29
		aem2008c01v1Mpx1Pres OBJECT-TYPE
			SYNTAX Bit0No1Yes
			MAX-ACCESS read-only
			STATUS current
			DESCRIPTION
				"It indicates the presence of MPX audio channels 1 to 8"
		::= { aem2008c01v1Entry 29 }

		-- 1.3.6.1.4.1.10106.3.101291.1.1.31
		aem2008c01v1Mpx2Pres OBJECT-TYPE
			SYNTAX Bit0No1Yes
			MAX-ACCESS read-only
			STATUS current
			DESCRIPTION
				"It indicates the presence of MPX audio channels 9 to 16"
		::= { aem2008c01v1Entry 31 }

		-- 1.3.6.1.4.1.10106.3.101291.1.1.33
		aem2008c01v1Mpx3Pres OBJECT-TYPE
			SYNTAX Bit0No1Yes
			MAX-ACCESS read-only
			STATUS current
			DESCRIPTION
				"It indicates the presence of MPX audio channels 17 to 24"
		::= { aem2008c01v1Entry 33 }

		-- 1.3.6.1.4.1.10106.3.101291.1.1.35
		aem2008c01v1Mpx4Pres OBJECT-TYPE
			SYNTAX Bit0No1Yes
			MAX-ACCESS read-only
			STATUS current
			DESCRIPTION
				"It indicates the presence of MPX audio channels 25 to 32"
		::= { aem2008c01v1Entry 35 }

		-- 1.3.6.1.4.1.10106.3.101291.1.1.37
		aem2008c01v1SerialNo OBJECT-TYPE
			SYNTAX SerialNo
			MAX-ACCESS read-only
			STATUS current
			DESCRIPTION
				"Serial number"
		::= { aem2008c01v1Entry 37 }

		-- 1.3.6.1.4.1.10106.3.101291.1.1.39
		aem2008c01v1Invert OBJECT-TYPE
			SYNTAX Bit0Yes1No
			MAX-ACCESS read-write
			STATUS current
			DESCRIPTION
				"It enables the signal inversion"
		::= { aem2008c01v1Entry 39 }

		-- 1.3.6.1.4.1.10106.3.101291.1.1.41
		aem2008c01v1Ref27mFail OBJECT-TYPE
			SYNTAX BitFail
			MAX-ACCESS read-only
			STATUS current
			DESCRIPTION
				"It indicates there is no 27 MHz reference signal"
		::= { aem2008c01v1Entry 41 }

		-- 1.3.6.1.4.1.10106.3.485001
		ade2008c01v1 OBJECT IDENTIFIER ::= { albalaProducts 485001 }

		-- 1.3.6.1.4.1.10106.3.485001.1
		ade2008c01v1Table  OBJECT-TYPE
			SYNTAX SEQUENCE OF Ade2008c01v1Entry
			MAX-ACCESS not-accessible
			STATUS current
			DESCRIPTION
				"Module  ADE2008C01V1 Table"
			::= { ade2008c01v1 1 }

		-- 1.3.6.1.4.1.10106.3.485001.1.1
		ade2008c01v1Entry  OBJECT-TYPE
			SYNTAX Ade2008c01v1Entry
			MAX-ACCESS not-accessible
			STATUS current
			DESCRIPTION
				"Module ADE2008C01V1 Entry"
			INDEX { ade2008c01v1Index }
			::= { ade2008c01v1Table 1 }

			Ade2008c01v1Entry ::=
			SEQUENCE {
				ade2008c01v1Index
				ModuleIndex,
				ade2008c01v1Section
				AudioChannels,
				ade2008c01v1FrqSamp
				Bit0481192,
				ade2008c01v1CleanH
				BitMask,
				ade2008c01v1CoarseGain
				LevelDbX6,
				ade2008c01v1SdiInFail
				BitFail,
				ade2008c01v1SdiInFailTrapEnable
				AlarmEnable,
				ade2008c01v1EdhInFail
				BitFail,
				ade2008c01v1EdhInFailTrapEnable
				AlarmEnable,
				ade2008c01v1AudFail
				BitFail,
				ade2008c01v1AudFailTrapEnable
				AlarmEnable,
				ade2008c01v1AudClip
				BitFail,
				ade2008c01v1AudClipTrapEnable
				AlarmEnable,
				ade2008c01v1Fmt
				Bit05251625,
				ade2008c01v1G1Pres
				Bit0No1Yes,
				ade2008c01v1G2Pres
				Bit0No1Yes,
				ade2008c01v1G3Pres
				Bit0No1Yes,
				ade2008c01v1G4Pres
				Bit0No1Yes,
				ade2008c01v1Mpx1Pres
				Bit0No1Yes,
				ade2008c01v1Mpx2Pres
				Bit0No1Yes,
				ade2008c01v1Mpx3Pres
				Bit0No1Yes,
				ade2008c01v1Mpx4Pres
				Bit0No1Yes,
				ade2008c01v1SerialNo
				SerialNo,
				ade2008c01v1Invert
				Bit0Yes1No
			 }

		-- 1.3.6.1.4.1.10106.3.101291.1.1.1
		ade2008c01v1Index OBJECT-TYPE
			SYNTAX ModuleIndex
			MAX-ACCESS read-only
			STATUS current
			DESCRIPTION
				"Index of ADE2008C01V1 Table"
		::= { ade2008c01v1Entry 1 }

		-- 1.3.6.1.4.1.10106.3.101291.1.1.3
		ade2008c01v1Section OBJECT-TYPE
			SYNTAX AudioChannels
			MAX-ACCESS read-write
			STATUS current
			DESCRIPTION
				"It selects the channels that will be deembedded"
		::= { ade2008c01v1Entry 3 }

		-- 1.3.6.1.4.1.10106.3.101291.1.1.5
		ade2008c01v1FrqSamp OBJECT-TYPE
			SYNTAX Bit0481192
			MAX-ACCESS read-write
			STATUS current
			DESCRIPTION
				"It selects the sampling frequency of the analogue sampling"
		::= { ade2008c01v1Entry 5 }

		-- 1.3.6.1.4.1.10106.3.101291.1.1.7
		ade2008c01v1CleanH OBJECT-TYPE
			SYNTAX BitMask
			MAX-ACCESS read-write
			STATUS current
			DESCRIPTION
				"It enables removing the ancillary packets in the horizontal blanking"
		::= { ade2008c01v1Entry 7 }

		-- 1.3.6.1.4.1.10106.3.101291.1.1.9
		ade2008c01v1CoarseGain OBJECT-TYPE
			SYNTAX LevelDbX6
			MAX-ACCESS read-write
			STATUS current
			DESCRIPTION
				"It selects the gain to apply to the analogue output"
		::= { ade2008c01v1Entry 9 }

		-- 1.3.6.1.4.1.10106.3.101291.1.1.11
		ade2008c01v1SdiInFail OBJECT-TYPE
			SYNTAX BitFail
			MAX-ACCESS read-only
			STATUS current
			DESCRIPTION
				"SDI input signal status"
		::= { ade2008c01v1Entry 11 }

		-- 1.3.6.1.4.1.10106.3.101291.1.1.12
		ade2008c01v1SdiInFailTrapEnable OBJECT-TYPE
			SYNTAX AlarmEnable
			MAX-ACCESS read-write
			STATUS current
			DESCRIPTION
				"SDI input signal status Trap Enable"
		::= { ade2008c01v1Entry 12 }

		-- 1.3.6.1.4.1.10106.3.101291.1.1.13
		ade2008c01v1EdhInFail OBJECT-TYPE
			SYNTAX BitFail
			MAX-ACCESS read-only
			STATUS current
			DESCRIPTION
				"It indicates EDH errors"
		::= { ade2008c01v1Entry 13 }

		-- 1.3.6.1.4.1.10106.3.101291.1.1.14
		ade2008c01v1EdhInFailTrapEnable OBJECT-TYPE
			SYNTAX AlarmEnable
			MAX-ACCESS read-write
			STATUS current
			DESCRIPTION
				"It indicates EDH errors Trap Enable"
		::= { ade2008c01v1Entry 14 }

		-- 1.3.6.1.4.1.10106.3.101291.1.1.15
		ade2008c01v1AudFail OBJECT-TYPE
			SYNTAX BitFail
			MAX-ACCESS read-only
			STATUS current
			DESCRIPTION
				"It indicates there are audio errors"
		::= { ade2008c01v1Entry 15 }

		-- 1.3.6.1.4.1.10106.3.101291.1.1.16
		ade2008c01v1AudFailTrapEnable OBJECT-TYPE
			SYNTAX AlarmEnable
			MAX-ACCESS read-write
			STATUS current
			DESCRIPTION
				"It indicates there are audio errors Trap Enable"
		::= { ade2008c01v1Entry 16 }

		-- 1.3.6.1.4.1.10106.3.101291.1.1.17
		ade2008c01v1AudClip OBJECT-TYPE
			SYNTAX BitFail
			MAX-ACCESS read-only
			STATUS current
			DESCRIPTION
				"It indicates there is digital clipping due to applied gain"
		::= { ade2008c01v1Entry 17 }

		-- 1.3.6.1.4.1.10106.3.101291.1.1.18
		ade2008c01v1AudClipTrapEnable OBJECT-TYPE
			SYNTAX AlarmEnable
			MAX-ACCESS read-write
			STATUS current
			DESCRIPTION
				"It indicates there is digital clipping due to applied gain Trap Enable"
		::= { ade2008c01v1Entry 18 }

		-- 1.3.6.1.4.1.10106.3.101291.1.1.19
		ade2008c01v1Fmt OBJECT-TYPE
			SYNTAX Bit05251625
			MAX-ACCESS read-only
			STATUS current
			DESCRIPTION
				"It indicates the SDI format"
		::= { ade2008c01v1Entry 19 }

		-- 1.3.6.1.4.1.10106.3.101291.1.1.21
		ade2008c01v1G1Pres OBJECT-TYPE
			SYNTAX Bit0No1Yes
			MAX-ACCESS read-only
			STATUS current
			DESCRIPTION
				"It indicates the presence of packets of audio group 1"
		::= { ade2008c01v1Entry 21 }

		-- 1.3.6.1.4.1.10106.3.101291.1.1.23
		ade2008c01v1G2Pres OBJECT-TYPE
			SYNTAX Bit0No1Yes
			MAX-ACCESS read-only
			STATUS current
			DESCRIPTION
				"It indicates the presence of packets of audio group 2"
		::= { ade2008c01v1Entry 23 }

		-- 1.3.6.1.4.1.10106.3.101291.1.1.25
		ade2008c01v1G3Pres OBJECT-TYPE
			SYNTAX Bit0No1Yes
			MAX-ACCESS read-only
			STATUS current
			DESCRIPTION
				"It indicates the presence of packets of audio group 3"
		::= { ade2008c01v1Entry 25 }

		-- 1.3.6.1.4.1.10106.3.101291.1.1.27
		ade2008c01v1G4Pres OBJECT-TYPE
			SYNTAX Bit0No1Yes
			MAX-ACCESS read-only
			STATUS current
			DESCRIPTION
				"It indicates the presence of packets of audio group 4"
		::= { ade2008c01v1Entry 27 }

		-- 1.3.6.1.4.1.10106.3.101291.1.1.29
		ade2008c01v1Mpx1Pres OBJECT-TYPE
			SYNTAX Bit0No1Yes
			MAX-ACCESS read-only
			STATUS current
			DESCRIPTION
				"It indicates the presence of MPX audio channels 1 to 8"
		::= { ade2008c01v1Entry 29 }

		-- 1.3.6.1.4.1.10106.3.101291.1.1.31
		ade2008c01v1Mpx2Pres OBJECT-TYPE
			SYNTAX Bit0No1Yes
			MAX-ACCESS read-only
			STATUS current
			DESCRIPTION
				"It indicates the presence of MPX audio channels 9 to 16"
		::= { ade2008c01v1Entry 31 }

		-- 1.3.6.1.4.1.10106.3.101291.1.1.33
		ade2008c01v1Mpx3Pres OBJECT-TYPE
			SYNTAX Bit0No1Yes
			MAX-ACCESS read-only
			STATUS current
			DESCRIPTION
				"It indicates the presence of MPX audio channels 17 to 24"
		::= { ade2008c01v1Entry 33 }

		-- 1.3.6.1.4.1.10106.3.101291.1.1.35
		ade2008c01v1Mpx4Pres OBJECT-TYPE
			SYNTAX Bit0No1Yes
			MAX-ACCESS read-only
			STATUS current
			DESCRIPTION
				"It indicates the presence of MPX audio channels 25 to 32"
		::= { ade2008c01v1Entry 35 }

		-- 1.3.6.1.4.1.10106.3.101291.1.1.37
		ade2008c01v1SerialNo OBJECT-TYPE
			SYNTAX SerialNo
			MAX-ACCESS read-only
			STATUS current
			DESCRIPTION
				"Serial number"
		::= { ade2008c01v1Entry 37 }

		-- 1.3.6.1.4.1.10106.3.101291.1.1.39
		ade2008c01v1Invert OBJECT-TYPE
			SYNTAX Bit0Yes1No
			MAX-ACCESS read-write
			STATUS current
			DESCRIPTION
				"It enables the signal inversion"
		::= { ade2008c01v1Entry 39 }

		-- 1.3.6.1.4.1.10106.3.485901
		htg3001c01v1 OBJECT IDENTIFIER ::= { albalaProducts 485901 }

		-- 1.3.6.1.4.1.10106.3.485901.1
		htg3001c01v1Table  OBJECT-TYPE
			SYNTAX SEQUENCE OF Htg3001c01v1Entry
			MAX-ACCESS not-accessible
			STATUS current
			DESCRIPTION
				"Module  HTG3001C01V1 Table"
			::= { htg3001c01v1 1 }

		-- 1.3.6.1.4.1.10106.3.485901.1.1
		htg3001c01v1Entry  OBJECT-TYPE
			SYNTAX Htg3001c01v1Entry
			MAX-ACCESS not-accessible
			STATUS current
			DESCRIPTION
				"Module HTG3001C01V1 Entry"
			INDEX { htg3001c01v1Index }
			::= { htg3001c01v1Table 1 }

			Htg3001c01v1Entry ::=
			SEQUENCE {
				htg3001c01v1Index
				ModuleIndex,
				htg3001c01v1ExpRefFormat
				SdiHd3gFmt6,
				htg3001c01v1ExpRefFormatTrapEnable
				AlarmEnable,
				htg3001c01v1RefInput
				RefSel1,
				htg3001c01v1RefInputTrapEnable
				AlarmEnable,
				htg3001c01v1MeasInput
				RefSel1,
				htg3001c01v1OutFormat1
				SdiHd3gFmt6,
				htg3001c01v1OutFormat1TrapEnable
				AlarmEnable,
				htg3001c01v1OutMute1
				Bit0No1Yes,
				htg3001c01v1HDelay1
				DelayPixel4,
				htg3001c01v1VDelay1
				DelayLines2,
				htg3001c01v1TestSignal1
				Uint5,
				htg3001c01v1EnGrp1Aud1
				Bit0No1Yes,
				htg3001c01v1EnGrp2Aud1
				Bit0No1Yes,
				htg3001c01v1EnGrp3Aud1
				Bit0No1Yes,
				htg3001c01v1EnGrp4Aud1
				Bit0No1Yes,
				htg3001c01v1EnOsd1
				Bit0No1Yes,
				htg3001c01v1AudFrP0G01
				AudioFreq1,
				htg3001c01v1AudFrP1G01
				AudioFreq1,
				htg3001c01v1AudFrP0G11
				AudioFreq1,
				htg3001c01v1AudFrP1G11
				AudioFreq1,
				htg3001c01v1AudFrP0G21
				AudioFreq1,
				htg3001c01v1AudFrP1G21
				AudioFreq1,
				htg3001c01v1AudFrP0G31
				AudioFreq1,
				htg3001c01v1AudFrP1G31
				AudioFreq1,
				htg3001c01v1AudDipP0G01
				Bit0Dis1Ena,
				htg3001c01v1AudDipP1G01
				Bit0Dis1Ena,
				htg3001c01v1AudDipP0G11
				Bit0Dis1Ena,
				htg3001c01v1AudDipP1G11
				Bit0Dis1Ena,
				htg3001c01v1AudDipP0G21
				Bit0Dis1Ena,
				htg3001c01v1AudDipP1G21
				Bit0Dis1Ena,
				htg3001c01v1AudDipP0G31
				Bit0Dis1Ena,
				htg3001c01v1AudDipP1G31
				Bit0Dis1Ena,
				htg3001c01v1AudLevP0G01
				AudioLev0,
				htg3001c01v1AudLevP0G11
				AudioLev0,
				htg3001c01v1AudLevP1G01
				AudioLev0,
				htg3001c01v1AudLevP1G11
				AudioLev0,
				htg3001c01v1AudLevP0G21
				AudioLev0,
				htg3001c01v1AudLevP1G21
				AudioLev0,
				htg3001c01v1AudLevP0G31
				AudioLev0,
				htg3001c01v1AudLevP1G31
				AudioLev0,
				htg3001c01v1OutFormat2
				SdiHd3gFmt6,
				htg3001c01v1OutFormat2TrapEnable
				AlarmEnable,
				htg3001c01v1OutMute2
				Bit0No1Yes,
				htg3001c01v1HDelay2
				DelayPixel4,
				htg3001c01v1VDelay2
				DelayLines2,
				htg3001c01v1TestSignal2
				Uint5,
				htg3001c01v1EnGrp1Aud2
				Bit0No1Yes,
				htg3001c01v1EnGrp2Aud2
				Bit0No1Yes,
				htg3001c01v1EnGrp3Aud2
				Bit0No1Yes,
				htg3001c01v1EnGrp4Aud2
				Bit0No1Yes,
				htg3001c01v1EnOsd2
				Bit0No1Yes,
				htg3001c01v1AudFrP0G02
				AudioFreq1,
				htg3001c01v1AudFrP1G02
				AudioFreq1,
				htg3001c01v1AudFrP0G12
				AudioFreq1,
				htg3001c01v1AudFrP1G12
				AudioFreq1,
				htg3001c01v1AudFrP0G22
				AudioFreq1,
				htg3001c01v1AudFrP1G22
				AudioFreq1,
				htg3001c01v1AudFrP0G32
				AudioFreq1,
				htg3001c01v1AudFrP1G32
				AudioFreq1,
				htg3001c01v1AudDipP0G02
				Bit0Dis1Ena,
				htg3001c01v1AudDipP1G02
				Bit0Dis1Ena,
				htg3001c01v1AudDipP0G12
				Bit0Dis1Ena,
				htg3001c01v1AudDipP1G12
				Bit0Dis1Ena,
				htg3001c01v1AudDipP0G22
				Bit0Dis1Ena,
				htg3001c01v1AudDipP1G22
				Bit0Dis1Ena,
				htg3001c01v1AudDipP0G32
				Bit0Dis1Ena,
				htg3001c01v1AudDipP1G32
				Bit0Dis1Ena,
				htg3001c01v1AudLevP0G02
				AudioLev0,
				htg3001c01v1AudLevP0G12
				AudioLev0,
				htg3001c01v1AudLevP1G02
				AudioLev0,
				htg3001c01v1AudLevP1G12
				AudioLev0,
				htg3001c01v1AudLevP0G22
				AudioLev0,
				htg3001c01v1AudLevP1G22
				AudioLev0,
				htg3001c01v1AudLevP0G32
				AudioLev0,
				htg3001c01v1AudLevP1G32
				AudioLev0,
				htg3001c01v1OutFormat3
				SdiHd3gFmt6,
				htg3001c01v1OutFormat3TrapEnable
				AlarmEnable,
				htg3001c01v1HDelay3
				DelayX74Ns,
				htg3001c01v1VDelay3
				DelayLines2,
				htg3001c01v1Sch3
				Sch3,
				htg3001c01v1ArefFailMsk
				BitMask,
				htg3001c01v1DrefFailMsk
				BitMask,
				htg3001c01v1IrefFailMsk
				BitMask,
				htg3001c01v1RefIncFailMsk
				BitMask,
				htg3001c01v1RefLckFailMsk
				BitMask,
				htg3001c01v1SumMonthSt
				Month,
				htg3001c01v1SumWeekSt
				WeekOfMonth,
				htg3001c01v1SumWDaySt
				Day,
				htg3001c01v1SumHourSt
				TimeH1,
				htg3001c01v1SumHourOffset
				Int8,
				htg3001c01v1WinMonthSt
				Month,
				htg3001c01v1WinWeekSt
				WeekOfMonth,
				htg3001c01v1WinWDaySt
				Day,
				htg3001c01v1WinHourSt
				TimeH1,
				htg3001c01v1WinHourOffset
				Int8,
				htg3001c01v1EnDlsave
				BitMask,
				htg3001c01v1DropFrame
				BitMask,
				htg3001c01v1Bgf
				BgfBits,
				htg3001c01v1DateFormat
				DateFmt,
				htg3001c01v1EnDateGen
				BitMask,
				htg3001c01v1AdjHourDay
				Uint5,
				htg3001c01v1ArefFail
				BitFail,
				htg3001c01v1ArefFailTrapEnable
				AlarmEnable,
				htg3001c01v1DrefFail
				BitFail,
				htg3001c01v1DrefFailTrapEnable
				AlarmEnable,
				htg3001c01v1IrefFail
				BitFail,
				htg3001c01v1IrefFailTrapEnable
				AlarmEnable,
				htg3001c01v1RefIncFail
				BitFail,
				htg3001c01v1RefIncFailTrapEnable
				AlarmEnable,
				htg3001c01v1RefLockFail
				BitFail,
				htg3001c01v1RefLockFailTrapEnable
				AlarmEnable,
				htg3001c01v1DrefCrcFail
				BitFail,
				htg3001c01v1DrefCrcFailTrapEnable
				AlarmEnable,
				htg3001c01v1TcFail
				BitFail,
				htg3001c01v1ArefFormat
				SdiHd3gFmt3,
				htg3001c01v1ArefFormatTrapEnable
				AlarmEnable,
				htg3001c01v1DrefFormat
				SdiHd3gFmt3,
				htg3001c01v1DrefFormatTrapEnable
				AlarmEnable,
				htg3001c01v1MeasDelay
				DelayX74Ns,
				htg3001c01v1MeasFreq
				FrqDrft3,
				htg3001c01v1SerialNo
				SerialNo,
				htg3001c01v1OsdDly1
				Bit0No1Yes,
				htg3001c01v1OsdDly2
				Bit0No1Yes,
				htg3001c01v1AvDlyBlack
				LumaUint8,
				htg3001c01v1AvDlySil
				LevelDbfs2x,
				htg3001c01v1DelayG1p0l
				DelayX1Ms,
				htg3001c01v1DelayG1p0r
				DelayX1Ms,
				htg3001c01v1DelayG1p1l
				DelayX1Ms,
				htg3001c01v1DelayG1p1r
				DelayX1Ms,
				htg3001c01v1DelayG2p0l
				DelayX1Ms,
				htg3001c01v1DelayG2p0r
				DelayX1Ms,
				htg3001c01v1DelayG2p1l
				DelayX1Ms,
				htg3001c01v1DelayG2p1r
				DelayX1Ms,
				htg3001c01v1DelayG3p0l
				DelayX1Ms,
				htg3001c01v1DelayG3p0r
				DelayX1Ms,
				htg3001c01v1DelayG3p1l
				DelayX1Ms,
				htg3001c01v1DelayG3p1r
				DelayX1Ms,
				htg3001c01v1DelayG4p0l
				DelayX1Ms,
				htg3001c01v1DelayG4p0r
				DelayX1Ms,
				htg3001c01v1DelayG4p1l
				DelayX1Ms,
				htg3001c01v1DelayG4p1r
				DelayX1Ms,
				htg3001c01v1AvSeqG1p0
				BitFail,
				htg3001c01v1AvSeqG1p1
				BitFail,
				htg3001c01v1AvSeqG2p0
				BitFail,
				htg3001c01v1AvSeqG2p1
				BitFail,
				htg3001c01v1AvSeqG3p0
				BitFail,
				htg3001c01v1AvSeqG3p1
				BitFail,
				htg3001c01v1AvSeqG4p0
				BitFail,
				htg3001c01v1AvSeqG4p1
				BitFail,
				htg3001c01v1AudGrpPres1
				BitFailN,
				htg3001c01v1AudGrpPres2
				BitFailN,
				htg3001c01v1AudGrpPres3
				BitFailN,
				htg3001c01v1AudGrpPres4
				BitFailN,
				htg3001c01v1AvSeqPhase
				Uint8
			 }

		-- 1.3.6.1.4.1.10106.3.101291.1.1.1
		htg3001c01v1Index OBJECT-TYPE
			SYNTAX ModuleIndex
			MAX-ACCESS read-only
			STATUS current
			DESCRIPTION
				"Index of HTG3001C01V1 Table"
		::= { htg3001c01v1Entry 1 }

		-- 1.3.6.1.4.1.10106.3.101291.1.1.3
		htg3001c01v1ExpRefFormat OBJECT-TYPE
			SYNTAX SdiHd3gFmt6
			MAX-ACCESS read-write
			STATUS current
			DESCRIPTION
				"Allows selecting the expected format of the reference"
		::= { htg3001c01v1Entry 3 }

		-- 1.3.6.1.4.1.10106.3.101291.1.1.4
		htg3001c01v1ExpRefFormatTrapEnable OBJECT-TYPE
			SYNTAX AlarmEnable
			MAX-ACCESS read-write
			STATUS current
			DESCRIPTION
				"Allows selecting the expected format of the reference Trap Enable"
		::= { htg3001c01v1Entry 4 }

		-- 1.3.6.1.4.1.10106.3.101291.1.1.5
		htg3001c01v1RefInput OBJECT-TYPE
			SYNTAX RefSel1
			MAX-ACCESS read-write
			STATUS current
			DESCRIPTION
				"Allows selecting the reference input"
		::= { htg3001c01v1Entry 5 }

		-- 1.3.6.1.4.1.10106.3.101291.1.1.6
		htg3001c01v1RefInputTrapEnable OBJECT-TYPE
			SYNTAX AlarmEnable
			MAX-ACCESS read-write
			STATUS current
			DESCRIPTION
				"Allows selecting the reference input Trap Enable"
		::= { htg3001c01v1Entry 6 }

		-- 1.3.6.1.4.1.10106.3.101291.1.1.7
		htg3001c01v1MeasInput OBJECT-TYPE
			SYNTAX RefSel1
			MAX-ACCESS read-write
			STATUS current
			DESCRIPTION
				"Allows selecting the input used for delay mesaurement"
		::= { htg3001c01v1Entry 7 }

		-- 1.3.6.1.4.1.10106.3.101291.1.1.9
		htg3001c01v1OutFormat1 OBJECT-TYPE
			SYNTAX SdiHd3gFmt6
			MAX-ACCESS read-write
			STATUS current
			DESCRIPTION
				"Allows selecting the output format"
		::= { htg3001c01v1Entry 9 }

		-- 1.3.6.1.4.1.10106.3.101291.1.1.10
		htg3001c01v1OutFormat1TrapEnable OBJECT-TYPE
			SYNTAX AlarmEnable
			MAX-ACCESS read-write
			STATUS current
			DESCRIPTION
				"Allows selecting the output format Trap Enable"
		::= { htg3001c01v1Entry 10 }

		-- 1.3.6.1.4.1.10106.3.101291.1.1.11
		htg3001c01v1OutMute1 OBJECT-TYPE
			SYNTAX Bit0No1Yes
			MAX-ACCESS read-write
			STATUS current
			DESCRIPTION
				"Allows disabling the output"
		::= { htg3001c01v1Entry 11 }

		-- 1.3.6.1.4.1.10106.3.101291.1.1.13
		htg3001c01v1HDelay1 OBJECT-TYPE
			SYNTAX DelayPixel4
			MAX-ACCESS read-write
			STATUS current
			DESCRIPTION
				"Allows adjusting the video horizontal delay of main output"
		::= { htg3001c01v1Entry 13 }

		-- 1.3.6.1.4.1.10106.3.101291.1.1.15
		htg3001c01v1VDelay1 OBJECT-TYPE
			SYNTAX DelayLines2
			MAX-ACCESS read-write
			STATUS current
			DESCRIPTION
				"Allows adjusting the video vertical delay of main output"
		::= { htg3001c01v1Entry 15 }

		-- 1.3.6.1.4.1.10106.3.101291.1.1.17
		htg3001c01v1TestSignal1 OBJECT-TYPE
			SYNTAX Uint5
			MAX-ACCESS read-write
			STATUS current
			DESCRIPTION
				"Allows selecting the generated video signal pattern"
		::= { htg3001c01v1Entry 17 }

		-- 1.3.6.1.4.1.10106.3.101291.1.1.19
		htg3001c01v1EnGrp1Aud1 OBJECT-TYPE
			SYNTAX Bit0No1Yes
			MAX-ACCESS read-write
			STATUS current
			DESCRIPTION
				"Allows inserting group 1 audio packets"
		::= { htg3001c01v1Entry 19 }

		-- 1.3.6.1.4.1.10106.3.101291.1.1.21
		htg3001c01v1EnGrp2Aud1 OBJECT-TYPE
			SYNTAX Bit0No1Yes
			MAX-ACCESS read-write
			STATUS current
			DESCRIPTION
				"Allows inserting group 2 audio packets"
		::= { htg3001c01v1Entry 21 }

		-- 1.3.6.1.4.1.10106.3.101291.1.1.23
		htg3001c01v1EnGrp3Aud1 OBJECT-TYPE
			SYNTAX Bit0No1Yes
			MAX-ACCESS read-write
			STATUS current
			DESCRIPTION
				"Allows inserting group 3 audio packets"
		::= { htg3001c01v1Entry 23 }

		-- 1.3.6.1.4.1.10106.3.101291.1.1.25
		htg3001c01v1EnGrp4Aud1 OBJECT-TYPE
			SYNTAX Bit0No1Yes
			MAX-ACCESS read-write
			STATUS current
			DESCRIPTION
				"Allows inserting group 4 audio packets"
		::= { htg3001c01v1Entry 25 }

		-- 1.3.6.1.4.1.10106.3.101291.1.1.27
		htg3001c01v1EnOsd1 OBJECT-TYPE
			SYNTAX Bit0No1Yes
			MAX-ACCESS read-write
			STATUS current
			DESCRIPTION
				"Allows inserting on sreen display caption"
		::= { htg3001c01v1Entry 27 }

		-- 1.3.6.1.4.1.10106.3.101291.1.1.29
		htg3001c01v1AudFrP0G01 OBJECT-TYPE
			SYNTAX AudioFreq1
			MAX-ACCESS read-write
			STATUS current
			DESCRIPTION
				"Allows selecting the audio signal in pair 0 group 1"
		::= { htg3001c01v1Entry 29 }

		-- 1.3.6.1.4.1.10106.3.101291.1.1.31
		htg3001c01v1AudFrP1G01 OBJECT-TYPE
			SYNTAX AudioFreq1
			MAX-ACCESS read-write
			STATUS current
			DESCRIPTION
				"Allows selecting the audio signal in pair 1 group 1"
		::= { htg3001c01v1Entry 31 }

		-- 1.3.6.1.4.1.10106.3.101291.1.1.33
		htg3001c01v1AudFrP0G11 OBJECT-TYPE
			SYNTAX AudioFreq1
			MAX-ACCESS read-write
			STATUS current
			DESCRIPTION
				"Allows selecting the audio signal in pair 0 group 2"
		::= { htg3001c01v1Entry 33 }

		-- 1.3.6.1.4.1.10106.3.101291.1.1.35
		htg3001c01v1AudFrP1G11 OBJECT-TYPE
			SYNTAX AudioFreq1
			MAX-ACCESS read-write
			STATUS current
			DESCRIPTION
				"Allows selecting the audio signal in pair 1 group 2"
		::= { htg3001c01v1Entry 35 }

		-- 1.3.6.1.4.1.10106.3.101291.1.1.37
		htg3001c01v1AudFrP0G21 OBJECT-TYPE
			SYNTAX AudioFreq1
			MAX-ACCESS read-write
			STATUS current
			DESCRIPTION
				"Allows selecting the audio signal in pair 0 group 3"
		::= { htg3001c01v1Entry 37 }

		-- 1.3.6.1.4.1.10106.3.101291.1.1.39
		htg3001c01v1AudFrP1G21 OBJECT-TYPE
			SYNTAX AudioFreq1
			MAX-ACCESS read-write
			STATUS current
			DESCRIPTION
				"Allows selecting the audio signal in pair 1 group 3"
		::= { htg3001c01v1Entry 39 }

		-- 1.3.6.1.4.1.10106.3.101291.1.1.41
		htg3001c01v1AudFrP0G31 OBJECT-TYPE
			SYNTAX AudioFreq1
			MAX-ACCESS read-write
			STATUS current
			DESCRIPTION
				"Allows selecting the audio signal in pair 0 group 4"
		::= { htg3001c01v1Entry 41 }

		-- 1.3.6.1.4.1.10106.3.101291.1.1.43
		htg3001c01v1AudFrP1G31 OBJECT-TYPE
			SYNTAX AudioFreq1
			MAX-ACCESS read-write
			STATUS current
			DESCRIPTION
				"Allows selecting the audio signal in pair 1 group 4"
		::= { htg3001c01v1Entry 43 }

		-- 1.3.6.1.4.1.10106.3.101291.1.1.45
		htg3001c01v1AudDipP0G01 OBJECT-TYPE
			SYNTAX Bit0Dis1Ena
			MAX-ACCESS read-write
			STATUS current
			DESCRIPTION
				"Allows enabling the insertion of silences for channel identification in pair 0 group 1"
		::= { htg3001c01v1Entry 45 }

		-- 1.3.6.1.4.1.10106.3.101291.1.1.47
		htg3001c01v1AudDipP1G01 OBJECT-TYPE
			SYNTAX Bit0Dis1Ena
			MAX-ACCESS read-write
			STATUS current
			DESCRIPTION
				"Allows enabling the insertion of silences for channel identification in pair 1 group 1"
		::= { htg3001c01v1Entry 47 }

		-- 1.3.6.1.4.1.10106.3.101291.1.1.49
		htg3001c01v1AudDipP0G11 OBJECT-TYPE
			SYNTAX Bit0Dis1Ena
			MAX-ACCESS read-write
			STATUS current
			DESCRIPTION
				"Allows enabling the insertion of silences for channel identification in pair 0 group 2"
		::= { htg3001c01v1Entry 49 }

		-- 1.3.6.1.4.1.10106.3.101291.1.1.51
		htg3001c01v1AudDipP1G11 OBJECT-TYPE
			SYNTAX Bit0Dis1Ena
			MAX-ACCESS read-write
			STATUS current
			DESCRIPTION
				"Allows enabling the insertion of silences for channel identification in pair 1 group 2"
		::= { htg3001c01v1Entry 51 }

		-- 1.3.6.1.4.1.10106.3.101291.1.1.53
		htg3001c01v1AudDipP0G21 OBJECT-TYPE
			SYNTAX Bit0Dis1Ena
			MAX-ACCESS read-write
			STATUS current
			DESCRIPTION
				"Allows enabling the insertion of silences for channel identification in pair 0 group 3"
		::= { htg3001c01v1Entry 53 }

		-- 1.3.6.1.4.1.10106.3.101291.1.1.55
		htg3001c01v1AudDipP1G21 OBJECT-TYPE
			SYNTAX Bit0Dis1Ena
			MAX-ACCESS read-write
			STATUS current
			DESCRIPTION
				"Allows enabling the insertion of silences for channel identification in pair 1 group 3"
		::= { htg3001c01v1Entry 55 }

		-- 1.3.6.1.4.1.10106.3.101291.1.1.57
		htg3001c01v1AudDipP0G31 OBJECT-TYPE
			SYNTAX Bit0Dis1Ena
			MAX-ACCESS read-write
			STATUS current
			DESCRIPTION
				"Allows enabling the insertion of silences for channel identification in pair 0 group 4"
		::= { htg3001c01v1Entry 57 }

		-- 1.3.6.1.4.1.10106.3.101291.1.1.59
		htg3001c01v1AudDipP1G31 OBJECT-TYPE
			SYNTAX Bit0Dis1Ena
			MAX-ACCESS read-write
			STATUS current
			DESCRIPTION
				"Allows enabling the insertion of silences for channel identification in pair 1 group 4"
		::= { htg3001c01v1Entry 59 }

		-- 1.3.6.1.4.1.10106.3.101291.1.1.61
		htg3001c01v1AudLevP0G01 OBJECT-TYPE
			SYNTAX AudioLev0
			MAX-ACCESS read-write
			STATUS current
			DESCRIPTION
				"Allows selecting the audio level in pair 0 group 1"
		::= { htg3001c01v1Entry 61 }

		-- 1.3.6.1.4.1.10106.3.101291.1.1.63
		htg3001c01v1AudLevP0G11 OBJECT-TYPE
			SYNTAX AudioLev0
			MAX-ACCESS read-write
			STATUS current
			DESCRIPTION
				"Allows selecting the audio level in pair 1 group 1"
		::= { htg3001c01v1Entry 63 }

		-- 1.3.6.1.4.1.10106.3.101291.1.1.65
		htg3001c01v1AudLevP1G01 OBJECT-TYPE
			SYNTAX AudioLev0
			MAX-ACCESS read-write
			STATUS current
			DESCRIPTION
				"Allows selecting the audio level in pair 0 group 2"
		::= { htg3001c01v1Entry 65 }

		-- 1.3.6.1.4.1.10106.3.101291.1.1.67
		htg3001c01v1AudLevP1G11 OBJECT-TYPE
			SYNTAX AudioLev0
			MAX-ACCESS read-write
			STATUS current
			DESCRIPTION
				"Allows selecting the audio level in pair 1 group 2"
		::= { htg3001c01v1Entry 67 }

		-- 1.3.6.1.4.1.10106.3.101291.1.1.69
		htg3001c01v1AudLevP0G21 OBJECT-TYPE
			SYNTAX AudioLev0
			MAX-ACCESS read-write
			STATUS current
			DESCRIPTION
				"Allows selecting the audio level in pair 0 group 3"
		::= { htg3001c01v1Entry 69 }

		-- 1.3.6.1.4.1.10106.3.101291.1.1.71
		htg3001c01v1AudLevP1G21 OBJECT-TYPE
			SYNTAX AudioLev0
			MAX-ACCESS read-write
			STATUS current
			DESCRIPTION
				"Allows selecting the audio level in pair 1 group 3"
		::= { htg3001c01v1Entry 71 }

		-- 1.3.6.1.4.1.10106.3.101291.1.1.73
		htg3001c01v1AudLevP0G31 OBJECT-TYPE
			SYNTAX AudioLev0
			MAX-ACCESS read-write
			STATUS current
			DESCRIPTION
				"Allows selecting the audio level in pair 0 group 4"
		::= { htg3001c01v1Entry 73 }

		-- 1.3.6.1.4.1.10106.3.101291.1.1.75
		htg3001c01v1AudLevP1G31 OBJECT-TYPE
			SYNTAX AudioLev0
			MAX-ACCESS read-write
			STATUS current
			DESCRIPTION
				"Allows selecting the audio level in pair 1 group 4"
		::= { htg3001c01v1Entry 75 }

		-- 1.3.6.1.4.1.10106.3.101291.1.1.77
		htg3001c01v1OutFormat2 OBJECT-TYPE
			SYNTAX SdiHd3gFmt6
			MAX-ACCESS read-write
			STATUS current
			DESCRIPTION
				"Allows selecting the output format"
		::= { htg3001c01v1Entry 77 }

		-- 1.3.6.1.4.1.10106.3.101291.1.1.78
		htg3001c01v1OutFormat2TrapEnable OBJECT-TYPE
			SYNTAX AlarmEnable
			MAX-ACCESS read-write
			STATUS current
			DESCRIPTION
				"Allows selecting the output format Trap Enable"
		::= { htg3001c01v1Entry 78 }

		-- 1.3.6.1.4.1.10106.3.101291.1.1.79
		htg3001c01v1OutMute2 OBJECT-TYPE
			SYNTAX Bit0No1Yes
			MAX-ACCESS read-write
			STATUS current
			DESCRIPTION
				"Allows disabling the output"
		::= { htg3001c01v1Entry 79 }

		-- 1.3.6.1.4.1.10106.3.101291.1.1.81
		htg3001c01v1HDelay2 OBJECT-TYPE
			SYNTAX DelayPixel4
			MAX-ACCESS read-write
			STATUS current
			DESCRIPTION
				"Allows adjusting the video horizontal delay of main output"
		::= { htg3001c01v1Entry 81 }

		-- 1.3.6.1.4.1.10106.3.101291.1.1.83
		htg3001c01v1VDelay2 OBJECT-TYPE
			SYNTAX DelayLines2
			MAX-ACCESS read-write
			STATUS current
			DESCRIPTION
				"Allows adjusting the video vertical delay of main output"
		::= { htg3001c01v1Entry 83 }

		-- 1.3.6.1.4.1.10106.3.101291.1.1.85
		htg3001c01v1TestSignal2 OBJECT-TYPE
			SYNTAX Uint5
			MAX-ACCESS read-write
			STATUS current
			DESCRIPTION
				"Allows selecting the generated video signal pattern"
		::= { htg3001c01v1Entry 85 }

		-- 1.3.6.1.4.1.10106.3.101291.1.1.87
		htg3001c01v1EnGrp1Aud2 OBJECT-TYPE
			SYNTAX Bit0No1Yes
			MAX-ACCESS read-write
			STATUS current
			DESCRIPTION
				"Allows inserting group 1 audio packets"
		::= { htg3001c01v1Entry 87 }

		-- 1.3.6.1.4.1.10106.3.101291.1.1.89
		htg3001c01v1EnGrp2Aud2 OBJECT-TYPE
			SYNTAX Bit0No1Yes
			MAX-ACCESS read-write
			STATUS current
			DESCRIPTION
				"Allows inserting group 2 audio packets"
		::= { htg3001c01v1Entry 89 }

		-- 1.3.6.1.4.1.10106.3.101291.1.1.91
		htg3001c01v1EnGrp3Aud2 OBJECT-TYPE
			SYNTAX Bit0No1Yes
			MAX-ACCESS read-write
			STATUS current
			DESCRIPTION
				"Allows inserting group 3 audio packets"
		::= { htg3001c01v1Entry 91 }

		-- 1.3.6.1.4.1.10106.3.101291.1.1.93
		htg3001c01v1EnGrp4Aud2 OBJECT-TYPE
			SYNTAX Bit0No1Yes
			MAX-ACCESS read-write
			STATUS current
			DESCRIPTION
				"Allows inserting group 4 audio packets"
		::= { htg3001c01v1Entry 93 }

		-- 1.3.6.1.4.1.10106.3.101291.1.1.95
		htg3001c01v1EnOsd2 OBJECT-TYPE
			SYNTAX Bit0No1Yes
			MAX-ACCESS read-write
			STATUS current
			DESCRIPTION
				"Allows inserting on sreen display caption"
		::= { htg3001c01v1Entry 95 }

		-- 1.3.6.1.4.1.10106.3.101291.1.1.97
		htg3001c01v1AudFrP0G02 OBJECT-TYPE
			SYNTAX AudioFreq1
			MAX-ACCESS read-write
			STATUS current
			DESCRIPTION
				"Allows selecting the audio signal in pair 0 group 1"
		::= { htg3001c01v1Entry 97 }

		-- 1.3.6.1.4.1.10106.3.101291.1.1.99
		htg3001c01v1AudFrP1G02 OBJECT-TYPE
			SYNTAX AudioFreq1
			MAX-ACCESS read-write
			STATUS current
			DESCRIPTION
				"Allows selecting the audio signal in pair 1 group 1"
		::= { htg3001c01v1Entry 99 }

		-- 1.3.6.1.4.1.10106.3.101291.1.1.101
		htg3001c01v1AudFrP0G12 OBJECT-TYPE
			SYNTAX AudioFreq1
			MAX-ACCESS read-write
			STATUS current
			DESCRIPTION
				"Allows selecting the audio signal in pair 0 group 2"
		::= { htg3001c01v1Entry 101 }

		-- 1.3.6.1.4.1.10106.3.101291.1.1.103
		htg3001c01v1AudFrP1G12 OBJECT-TYPE
			SYNTAX AudioFreq1
			MAX-ACCESS read-write
			STATUS current
			DESCRIPTION
				"Allows selecting the audio signal in pair 1 group 2"
		::= { htg3001c01v1Entry 103 }

		-- 1.3.6.1.4.1.10106.3.101291.1.1.105
		htg3001c01v1AudFrP0G22 OBJECT-TYPE
			SYNTAX AudioFreq1
			MAX-ACCESS read-write
			STATUS current
			DESCRIPTION
				"Allows selecting the audio signal in pair 0 group 3"
		::= { htg3001c01v1Entry 105 }

		-- 1.3.6.1.4.1.10106.3.101291.1.1.107
		htg3001c01v1AudFrP1G22 OBJECT-TYPE
			SYNTAX AudioFreq1
			MAX-ACCESS read-write
			STATUS current
			DESCRIPTION
				"Allows selecting the audio signal in pair 1 group 3"
		::= { htg3001c01v1Entry 107 }

		-- 1.3.6.1.4.1.10106.3.101291.1.1.109
		htg3001c01v1AudFrP0G32 OBJECT-TYPE
			SYNTAX AudioFreq1
			MAX-ACCESS read-write
			STATUS current
			DESCRIPTION
				"Allows selecting the audio signal in pair 0 group 4"
		::= { htg3001c01v1Entry 109 }

		-- 1.3.6.1.4.1.10106.3.101291.1.1.111
		htg3001c01v1AudFrP1G32 OBJECT-TYPE
			SYNTAX AudioFreq1
			MAX-ACCESS read-write
			STATUS current
			DESCRIPTION
				"Allows selecting the audio signal in pair 1 group 4"
		::= { htg3001c01v1Entry 111 }

		-- 1.3.6.1.4.1.10106.3.101291.1.1.113
		htg3001c01v1AudDipP0G02 OBJECT-TYPE
			SYNTAX Bit0Dis1Ena
			MAX-ACCESS read-write
			STATUS current
			DESCRIPTION
				"Allows enabling the insertion of silences for channel identification in pair 0 group 1"
		::= { htg3001c01v1Entry 113 }

		-- 1.3.6.1.4.1.10106.3.101291.1.1.115
		htg3001c01v1AudDipP1G02 OBJECT-TYPE
			SYNTAX Bit0Dis1Ena
			MAX-ACCESS read-write
			STATUS current
			DESCRIPTION
				"Allows enabling the insertion of silences for channel identification in pair 1 group 1"
		::= { htg3001c01v1Entry 115 }

		-- 1.3.6.1.4.1.10106.3.101291.1.1.117
		htg3001c01v1AudDipP0G12 OBJECT-TYPE
			SYNTAX Bit0Dis1Ena
			MAX-ACCESS read-write
			STATUS current
			DESCRIPTION
				"Allows enabling the insertion of silences for channel identification in pair 0 group 2"
		::= { htg3001c01v1Entry 117 }

		-- 1.3.6.1.4.1.10106.3.101291.1.1.119
		htg3001c01v1AudDipP1G12 OBJECT-TYPE
			SYNTAX Bit0Dis1Ena
			MAX-ACCESS read-write
			STATUS current
			DESCRIPTION
				"Allows enabling the insertion of silences for channel identification in pair 1 group 2"
		::= { htg3001c01v1Entry 119 }

		-- 1.3.6.1.4.1.10106.3.101291.1.1.121
		htg3001c01v1AudDipP0G22 OBJECT-TYPE
			SYNTAX Bit0Dis1Ena
			MAX-ACCESS read-write
			STATUS current
			DESCRIPTION
				"Allows enabling the insertion of silences for channel identification in pair 0 group 3"
		::= { htg3001c01v1Entry 121 }

		-- 1.3.6.1.4.1.10106.3.101291.1.1.123
		htg3001c01v1AudDipP1G22 OBJECT-TYPE
			SYNTAX Bit0Dis1Ena
			MAX-ACCESS read-write
			STATUS current
			DESCRIPTION
				"Allows enabling the insertion of silences for channel identification in pair 1 group 3"
		::= { htg3001c01v1Entry 123 }

		-- 1.3.6.1.4.1.10106.3.101291.1.1.125
		htg3001c01v1AudDipP0G32 OBJECT-TYPE
			SYNTAX Bit0Dis1Ena
			MAX-ACCESS read-write
			STATUS current
			DESCRIPTION
				"Allows enabling the insertion of silences for channel identification in pair 0 group 4"
		::= { htg3001c01v1Entry 125 }

		-- 1.3.6.1.4.1.10106.3.101291.1.1.127
		htg3001c01v1AudDipP1G32 OBJECT-TYPE
			SYNTAX Bit0Dis1Ena
			MAX-ACCESS read-write
			STATUS current
			DESCRIPTION
				"Allows enabling the insertion of silences for channel identification in pair 1 group 4"
		::= { htg3001c01v1Entry 127 }

		-- 1.3.6.1.4.1.10106.3.101291.1.1.129
		htg3001c01v1AudLevP0G02 OBJECT-TYPE
			SYNTAX AudioLev0
			MAX-ACCESS read-write
			STATUS current
			DESCRIPTION
				"Allows selecting the audio level in pair 0 group 1"
		::= { htg3001c01v1Entry 129 }

		-- 1.3.6.1.4.1.10106.3.101291.1.1.131
		htg3001c01v1AudLevP0G12 OBJECT-TYPE
			SYNTAX AudioLev0
			MAX-ACCESS read-write
			STATUS current
			DESCRIPTION
				"Allows selecting the audio level in pair 1 group 1"
		::= { htg3001c01v1Entry 131 }

		-- 1.3.6.1.4.1.10106.3.101291.1.1.133
		htg3001c01v1AudLevP1G02 OBJECT-TYPE
			SYNTAX AudioLev0
			MAX-ACCESS read-write
			STATUS current
			DESCRIPTION
				"Allows selecting the audio level in pair 0 group 2"
		::= { htg3001c01v1Entry 133 }

		-- 1.3.6.1.4.1.10106.3.101291.1.1.135
		htg3001c01v1AudLevP1G12 OBJECT-TYPE
			SYNTAX AudioLev0
			MAX-ACCESS read-write
			STATUS current
			DESCRIPTION
				"Allows selecting the audio level in pair 1 group 2"
		::= { htg3001c01v1Entry 135 }

		-- 1.3.6.1.4.1.10106.3.101291.1.1.137
		htg3001c01v1AudLevP0G22 OBJECT-TYPE
			SYNTAX AudioLev0
			MAX-ACCESS read-write
			STATUS current
			DESCRIPTION
				"Allows selecting the audio level in pair 0 group 3"
		::= { htg3001c01v1Entry 137 }

		-- 1.3.6.1.4.1.10106.3.101291.1.1.139
		htg3001c01v1AudLevP1G22 OBJECT-TYPE
			SYNTAX AudioLev0
			MAX-ACCESS read-write
			STATUS current
			DESCRIPTION
				"Allows selecting the audio level in pair 1 group 3"
		::= { htg3001c01v1Entry 139 }

		-- 1.3.6.1.4.1.10106.3.101291.1.1.141
		htg3001c01v1AudLevP0G32 OBJECT-TYPE
			SYNTAX AudioLev0
			MAX-ACCESS read-write
			STATUS current
			DESCRIPTION
				"Allows selecting the audio level in pair 0 group 4"
		::= { htg3001c01v1Entry 141 }

		-- 1.3.6.1.4.1.10106.3.101291.1.1.143
		htg3001c01v1AudLevP1G32 OBJECT-TYPE
			SYNTAX AudioLev0
			MAX-ACCESS read-write
			STATUS current
			DESCRIPTION
				"Allows selecting the audio level in pair 1 group 4"
		::= { htg3001c01v1Entry 143 }

		-- 1.3.6.1.4.1.10106.3.101291.1.1.145
		htg3001c01v1OutFormat3 OBJECT-TYPE
			SYNTAX SdiHd3gFmt6
			MAX-ACCESS read-write
			STATUS current
			DESCRIPTION
				"Allows selecting the output format"
		::= { htg3001c01v1Entry 145 }

		-- 1.3.6.1.4.1.10106.3.101291.1.1.146
		htg3001c01v1OutFormat3TrapEnable OBJECT-TYPE
			SYNTAX AlarmEnable
			MAX-ACCESS read-write
			STATUS current
			DESCRIPTION
				"Allows selecting the output format Trap Enable"
		::= { htg3001c01v1Entry 146 }

		-- 1.3.6.1.4.1.10106.3.101291.1.1.147
		htg3001c01v1HDelay3 OBJECT-TYPE
			SYNTAX DelayX74Ns
			MAX-ACCESS read-write
			STATUS current
			DESCRIPTION
				"Allows adjusting the video horizontal delay of main output"
		::= { htg3001c01v1Entry 147 }

		-- 1.3.6.1.4.1.10106.3.101291.1.1.149
		htg3001c01v1VDelay3 OBJECT-TYPE
			SYNTAX DelayLines2
			MAX-ACCESS read-write
			STATUS current
			DESCRIPTION
				"Allows adjusting the video vertical delay of main output"
		::= { htg3001c01v1Entry 149 }

		-- 1.3.6.1.4.1.10106.3.101291.1.1.151
		htg3001c01v1Sch3 OBJECT-TYPE
			SYNTAX Sch3
			MAX-ACCESS read-write
			STATUS current
			DESCRIPTION
				"Allows adjusting the SCH"
		::= { htg3001c01v1Entry 151 }

		-- 1.3.6.1.4.1.10106.3.101291.1.1.153
		htg3001c01v1ArefFailMsk OBJECT-TYPE
			SYNTAX BitMask
			MAX-ACCESS read-write
			STATUS current
			DESCRIPTION
				"Allows masking the analog reference absence fail"
		::= { htg3001c01v1Entry 153 }

		-- 1.3.6.1.4.1.10106.3.101291.1.1.155
		htg3001c01v1DrefFailMsk OBJECT-TYPE
			SYNTAX BitMask
			MAX-ACCESS read-write
			STATUS current
			DESCRIPTION
				"Allows masking the digital reference absence fail"
		::= { htg3001c01v1Entry 155 }

		-- 1.3.6.1.4.1.10106.3.101291.1.1.157
		htg3001c01v1IrefFailMsk OBJECT-TYPE
			SYNTAX BitMask
			MAX-ACCESS read-write
			STATUS current
			DESCRIPTION
				"Allows masking the internal reference absence fail"
		::= { htg3001c01v1Entry 157 }

		-- 1.3.6.1.4.1.10106.3.101291.1.1.159
		htg3001c01v1RefIncFailMsk OBJECT-TYPE
			SYNTAX BitMask
			MAX-ACCESS read-write
			STATUS current
			DESCRIPTION
				"Allows masking the different reference format fail"
		::= { htg3001c01v1Entry 159 }

		-- 1.3.6.1.4.1.10106.3.101291.1.1.161
		htg3001c01v1RefLckFailMsk OBJECT-TYPE
			SYNTAX BitMask
			MAX-ACCESS read-write
			STATUS current
			DESCRIPTION
				"Allows masking the reference lock fail"
		::= { htg3001c01v1Entry 161 }

		-- 1.3.6.1.4.1.10106.3.101291.1.1.163
		htg3001c01v1SumMonthSt OBJECT-TYPE
			SYNTAX Month
			MAX-ACCESS read-write
			STATUS current
			DESCRIPTION
				"It allows selecting the month when summer time starts"
		::= { htg3001c01v1Entry 163 }

		-- 1.3.6.1.4.1.10106.3.101291.1.1.165
		htg3001c01v1SumWeekSt OBJECT-TYPE
			SYNTAX WeekOfMonth
			MAX-ACCESS read-write
			STATUS current
			DESCRIPTION
				"It allows selecting the week of the month when summer time starts"
		::= { htg3001c01v1Entry 165 }

		-- 1.3.6.1.4.1.10106.3.101291.1.1.167
		htg3001c01v1SumWDaySt OBJECT-TYPE
			SYNTAX Day
			MAX-ACCESS read-write
			STATUS current
			DESCRIPTION
				"It allows selecting the week day when summer time starts"
		::= { htg3001c01v1Entry 167 }

		-- 1.3.6.1.4.1.10106.3.101291.1.1.169
		htg3001c01v1SumHourSt OBJECT-TYPE
			SYNTAX TimeH1
			MAX-ACCESS read-write
			STATUS current
			DESCRIPTION
				"It allows selecting the UTC hour when summer time starts"
		::= { htg3001c01v1Entry 169 }

		-- 1.3.6.1.4.1.10106.3.101291.1.1.171
		htg3001c01v1SumHourOffset OBJECT-TYPE
			SYNTAX Int8
			MAX-ACCESS read-write
			STATUS current
			DESCRIPTION
				"It allows selecting the local time offset at summer time"
		::= { htg3001c01v1Entry 171 }

		-- 1.3.6.1.4.1.10106.3.101291.1.1.173
		htg3001c01v1WinMonthSt OBJECT-TYPE
			SYNTAX Month
			MAX-ACCESS read-write
			STATUS current
			DESCRIPTION
				"It allows selecting the month when winter time starts"
		::= { htg3001c01v1Entry 173 }

		-- 1.3.6.1.4.1.10106.3.101291.1.1.175
		htg3001c01v1WinWeekSt OBJECT-TYPE
			SYNTAX WeekOfMonth
			MAX-ACCESS read-write
			STATUS current
			DESCRIPTION
				"It allows selecting the week of the month when winter time starts"
		::= { htg3001c01v1Entry 175 }

		-- 1.3.6.1.4.1.10106.3.101291.1.1.177
		htg3001c01v1WinWDaySt OBJECT-TYPE
			SYNTAX Day
			MAX-ACCESS read-write
			STATUS current
			DESCRIPTION
				"It allows selecting the week day when winter time starts"
		::= { htg3001c01v1Entry 177 }

		-- 1.3.6.1.4.1.10106.3.101291.1.1.179
		htg3001c01v1WinHourSt OBJECT-TYPE
			SYNTAX TimeH1
			MAX-ACCESS read-write
			STATUS current
			DESCRIPTION
				"It allows selecting the UTC hour when winter time starts"
		::= { htg3001c01v1Entry 179 }

		-- 1.3.6.1.4.1.10106.3.101291.1.1.181
		htg3001c01v1WinHourOffset OBJECT-TYPE
			SYNTAX Int8
			MAX-ACCESS read-write
			STATUS current
			DESCRIPTION
				"It allows selecting the local time offset at winter time"
		::= { htg3001c01v1Entry 181 }

		-- 1.3.6.1.4.1.10106.3.101291.1.1.183
		htg3001c01v1EnDlsave OBJECT-TYPE
			SYNTAX BitMask
			MAX-ACCESS read-write
			STATUS current
			DESCRIPTION
				"It allows enabling automatic daylight saving"
		::= { htg3001c01v1Entry 183 }

		-- 1.3.6.1.4.1.10106.3.101291.1.1.185
		htg3001c01v1DropFrame OBJECT-TYPE
			SYNTAX BitMask
			MAX-ACCESS read-write
			STATUS current
			DESCRIPTION
				"Enables time compensated mode in 59.94 Hz formats"
		::= { htg3001c01v1Entry 185 }

		-- 1.3.6.1.4.1.10106.3.101291.1.1.187
		htg3001c01v1Bgf OBJECT-TYPE
			SYNTAX BgfBits
			MAX-ACCESS read-write
			STATUS current
			DESCRIPTION
				"Contents of the binary group flags in the time code"
		::= { htg3001c01v1Entry 187 }

		-- 1.3.6.1.4.1.10106.3.101291.1.1.189
		htg3001c01v1DateFormat OBJECT-TYPE
			SYNTAX DateFmt
			MAX-ACCESS read-write
			STATUS current
			DESCRIPTION
				"Selects date format in the BGF (binary group flags)"
		::= { htg3001c01v1Entry 189 }

		-- 1.3.6.1.4.1.10106.3.101291.1.1.191
		htg3001c01v1EnDateGen OBJECT-TYPE
			SYNTAX BitMask
			MAX-ACCESS read-write
			STATUS current
			DESCRIPTION
				"Enables date insertion in time code"
		::= { htg3001c01v1Entry 191 }

		-- 1.3.6.1.4.1.10106.3.101291.1.1.193
		htg3001c01v1AdjHourDay OBJECT-TYPE
			SYNTAX Uint5
			MAX-ACCESS read-write
			STATUS current
			DESCRIPTION
				"Resets time code frame counter value at the end of this UTC hour (59.94 Hz formats only)"
		::= { htg3001c01v1Entry 193 }

		-- 1.3.6.1.4.1.10106.3.101291.1.1.195
		htg3001c01v1ArefFail OBJECT-TYPE
			SYNTAX BitFail
			MAX-ACCESS read-only
			STATUS current
			DESCRIPTION
				"Indicates the absence of analog reference"
		::= { htg3001c01v1Entry 195 }

		-- 1.3.6.1.4.1.10106.3.101291.1.1.196
		htg3001c01v1ArefFailTrapEnable OBJECT-TYPE
			SYNTAX AlarmEnable
			MAX-ACCESS read-write
			STATUS current
			DESCRIPTION
				"Indicates the absence of analog reference Trap Enable"
		::= { htg3001c01v1Entry 196 }

		-- 1.3.6.1.4.1.10106.3.101291.1.1.197
		htg3001c01v1DrefFail OBJECT-TYPE
			SYNTAX BitFail
			MAX-ACCESS read-only
			STATUS current
			DESCRIPTION
				"Indicates the absence of digital reference"
		::= { htg3001c01v1Entry 197 }

		-- 1.3.6.1.4.1.10106.3.101291.1.1.198
		htg3001c01v1DrefFailTrapEnable OBJECT-TYPE
			SYNTAX AlarmEnable
			MAX-ACCESS read-write
			STATUS current
			DESCRIPTION
				"Indicates the absence of digital reference Trap Enable"
		::= { htg3001c01v1Entry 198 }

		-- 1.3.6.1.4.1.10106.3.101291.1.1.199
		htg3001c01v1IrefFail OBJECT-TYPE
			SYNTAX BitFail
			MAX-ACCESS read-only
			STATUS current
			DESCRIPTION
				"Indicates the absence of internal reference"
		::= { htg3001c01v1Entry 199 }

		-- 1.3.6.1.4.1.10106.3.101291.1.1.200
		htg3001c01v1IrefFailTrapEnable OBJECT-TYPE
			SYNTAX AlarmEnable
			MAX-ACCESS read-write
			STATUS current
			DESCRIPTION
				"Indicates the absence of internal reference Trap Enable"
		::= { htg3001c01v1Entry 200 }

		-- 1.3.6.1.4.1.10106.3.101291.1.1.201
		htg3001c01v1RefIncFail OBJECT-TYPE
			SYNTAX BitFail
			MAX-ACCESS read-only
			STATUS current
			DESCRIPTION
				"Indicates that the format of the received reference is different from expected"
		::= { htg3001c01v1Entry 201 }

		-- 1.3.6.1.4.1.10106.3.101291.1.1.202
		htg3001c01v1RefIncFailTrapEnable OBJECT-TYPE
			SYNTAX AlarmEnable
			MAX-ACCESS read-write
			STATUS current
			DESCRIPTION
				"Indicates that the format of the received reference is different from expected Trap Enable"
		::= { htg3001c01v1Entry 202 }

		-- 1.3.6.1.4.1.10106.3.101291.1.1.203
		htg3001c01v1RefLockFail OBJECT-TYPE
			SYNTAX BitFail
			MAX-ACCESS read-only
			STATUS current
			DESCRIPTION
				"Indicates that the module is not locked to the reference"
		::= { htg3001c01v1Entry 203 }

		-- 1.3.6.1.4.1.10106.3.101291.1.1.204
		htg3001c01v1RefLockFailTrapEnable OBJECT-TYPE
			SYNTAX AlarmEnable
			MAX-ACCESS read-write
			STATUS current
			DESCRIPTION
				"Indicates that the module is not locked to the reference Trap Enable"
		::= { htg3001c01v1Entry 204 }

		-- 1.3.6.1.4.1.10106.3.101291.1.1.205
		htg3001c01v1DrefCrcFail OBJECT-TYPE
			SYNTAX BitFail
			MAX-ACCESS read-only
			STATUS current
			DESCRIPTION
				"Indicates that the digital reference has CRC/EDH errors"
		::= { htg3001c01v1Entry 205 }

		-- 1.3.6.1.4.1.10106.3.101291.1.1.206
		htg3001c01v1DrefCrcFailTrapEnable OBJECT-TYPE
			SYNTAX AlarmEnable
			MAX-ACCESS read-write
			STATUS current
			DESCRIPTION
				"Indicates that the digital reference has CRC/EDH errors Trap Enable"
		::= { htg3001c01v1Entry 206 }

		-- 1.3.6.1.4.1.10106.3.101291.1.1.207
		htg3001c01v1TcFail OBJECT-TYPE
			SYNTAX BitFail
			MAX-ACCESS read-only
			STATUS current
			DESCRIPTION
				"Indicates the absence of time and date information in the internal reference"
		::= { htg3001c01v1Entry 207 }

		-- 1.3.6.1.4.1.10106.3.101291.1.1.209
		htg3001c01v1ArefFormat OBJECT-TYPE
			SYNTAX SdiHd3gFmt3
			MAX-ACCESS read-only
			STATUS current
			DESCRIPTION
				"Indicates the detected format of the analog reference"
		::= { htg3001c01v1Entry 209 }

		-- 1.3.6.1.4.1.10106.3.101291.1.1.210
		htg3001c01v1ArefFormatTrapEnable OBJECT-TYPE
			SYNTAX AlarmEnable
			MAX-ACCESS read-write
			STATUS current
			DESCRIPTION
				"Indicates the detected format of the analog reference Trap Enable"
		::= { htg3001c01v1Entry 210 }

		-- 1.3.6.1.4.1.10106.3.101291.1.1.211
		htg3001c01v1DrefFormat OBJECT-TYPE
			SYNTAX SdiHd3gFmt3
			MAX-ACCESS read-only
			STATUS current
			DESCRIPTION
				"Indicates the detected format of the digital reference"
		::= { htg3001c01v1Entry 211 }

		-- 1.3.6.1.4.1.10106.3.101291.1.1.212
		htg3001c01v1DrefFormatTrapEnable OBJECT-TYPE
			SYNTAX AlarmEnable
			MAX-ACCESS read-write
			STATUS current
			DESCRIPTION
				"Indicates the detected format of the digital reference Trap Enable"
		::= { htg3001c01v1Entry 212 }

		-- 1.3.6.1.4.1.10106.3.101291.1.1.213
		htg3001c01v1MeasDelay OBJECT-TYPE
			SYNTAX DelayX74Ns
			MAX-ACCESS read-only
			STATUS current
			DESCRIPTION
				"Indicates the delay measured between references"
		::= { htg3001c01v1Entry 213 }

		-- 1.3.6.1.4.1.10106.3.101291.1.1.215
		htg3001c01v1MeasFreq OBJECT-TYPE
			SYNTAX FrqDrft3
			MAX-ACCESS read-only
			STATUS current
			DESCRIPTION
				"Indicates the measured frequency deviation"
		::= { htg3001c01v1Entry 215 }

		-- 1.3.6.1.4.1.10106.3.101291.1.1.217
		htg3001c01v1SerialNo OBJECT-TYPE
			SYNTAX SerialNo
			MAX-ACCESS read-only
			STATUS current
			DESCRIPTION
				"Serial number"
		::= { htg3001c01v1Entry 217 }

		-- 1.3.6.1.4.1.10106.3.101291.1.1.219
		htg3001c01v1OsdDly1 OBJECT-TYPE
			SYNTAX Bit0No1Yes
			MAX-ACCESS read-write
			STATUS current
			DESCRIPTION
				"Shows A/V delays instead of the specified texts"
		::= { htg3001c01v1Entry 219 }

		-- 1.3.6.1.4.1.10106.3.101291.1.1.221
		htg3001c01v1OsdDly2 OBJECT-TYPE
			SYNTAX Bit0No1Yes
			MAX-ACCESS read-write
			STATUS current
			DESCRIPTION
				"Shows A/V delays instead of the specified texts"
		::= { htg3001c01v1Entry 221 }

		-- 1.3.6.1.4.1.10106.3.101291.1.1.223
		htg3001c01v1AvDlyBlack OBJECT-TYPE
			SYNTAX LumaUint8
			MAX-ACCESS read-write
			STATUS current
			DESCRIPTION
				"Maximum luminance value accepted for black frame detection"
		::= { htg3001c01v1Entry 223 }

		-- 1.3.6.1.4.1.10106.3.101291.1.1.225
		htg3001c01v1AvDlySil OBJECT-TYPE
			SYNTAX LevelDbfs2x
			MAX-ACCESS read-write
			STATUS current
			DESCRIPTION
				"Maximum audio level accepted for silence detection"
		::= { htg3001c01v1Entry 225 }

		-- 1.3.6.1.4.1.10106.3.101291.1.1.227
		htg3001c01v1DelayG1p0l OBJECT-TYPE
			SYNTAX DelayX1Ms
			MAX-ACCESS read-only
			STATUS current
			DESCRIPTION
				"A negative value implies that audio is advanced with respect to video"
		::= { htg3001c01v1Entry 227 }

		-- 1.3.6.1.4.1.10106.3.101291.1.1.229
		htg3001c01v1DelayG1p0r OBJECT-TYPE
			SYNTAX DelayX1Ms
			MAX-ACCESS read-only
			STATUS current
			DESCRIPTION
				"A negative value implies that audio is advanced with respect to video"
		::= { htg3001c01v1Entry 229 }

		-- 1.3.6.1.4.1.10106.3.101291.1.1.231
		htg3001c01v1DelayG1p1l OBJECT-TYPE
			SYNTAX DelayX1Ms
			MAX-ACCESS read-only
			STATUS current
			DESCRIPTION
				"A negative value implies that audio is advanced with respect to video"
		::= { htg3001c01v1Entry 231 }

		-- 1.3.6.1.4.1.10106.3.101291.1.1.233
		htg3001c01v1DelayG1p1r OBJECT-TYPE
			SYNTAX DelayX1Ms
			MAX-ACCESS read-only
			STATUS current
			DESCRIPTION
				"A negative value implies that audio is advanced with respect to video"
		::= { htg3001c01v1Entry 233 }

		-- 1.3.6.1.4.1.10106.3.101291.1.1.235
		htg3001c01v1DelayG2p0l OBJECT-TYPE
			SYNTAX DelayX1Ms
			MAX-ACCESS read-only
			STATUS current
			DESCRIPTION
				"A negative value implies that audio is advanced with respect to video"
		::= { htg3001c01v1Entry 235 }

		-- 1.3.6.1.4.1.10106.3.101291.1.1.237
		htg3001c01v1DelayG2p0r OBJECT-TYPE
			SYNTAX DelayX1Ms
			MAX-ACCESS read-only
			STATUS current
			DESCRIPTION
				"A negative value implies that audio is advanced with respect to video"
		::= { htg3001c01v1Entry 237 }

		-- 1.3.6.1.4.1.10106.3.101291.1.1.239
		htg3001c01v1DelayG2p1l OBJECT-TYPE
			SYNTAX DelayX1Ms
			MAX-ACCESS read-only
			STATUS current
			DESCRIPTION
				"A negative value implies that audio is advanced with respect to video"
		::= { htg3001c01v1Entry 239 }

		-- 1.3.6.1.4.1.10106.3.101291.1.1.241
		htg3001c01v1DelayG2p1r OBJECT-TYPE
			SYNTAX DelayX1Ms
			MAX-ACCESS read-only
			STATUS current
			DESCRIPTION
				"A negative value implies that audio is advanced with respect to video"
		::= { htg3001c01v1Entry 241 }

		-- 1.3.6.1.4.1.10106.3.101291.1.1.243
		htg3001c01v1DelayG3p0l OBJECT-TYPE
			SYNTAX DelayX1Ms
			MAX-ACCESS read-only
			STATUS current
			DESCRIPTION
				"A negative value implies that audio is advanced with respect to video"
		::= { htg3001c01v1Entry 243 }

		-- 1.3.6.1.4.1.10106.3.101291.1.1.245
		htg3001c01v1DelayG3p0r OBJECT-TYPE
			SYNTAX DelayX1Ms
			MAX-ACCESS read-only
			STATUS current
			DESCRIPTION
				"A negative value implies that audio is advanced with respect to video"
		::= { htg3001c01v1Entry 245 }

		-- 1.3.6.1.4.1.10106.3.101291.1.1.247
		htg3001c01v1DelayG3p1l OBJECT-TYPE
			SYNTAX DelayX1Ms
			MAX-ACCESS read-only
			STATUS current
			DESCRIPTION
				"A negative value implies that audio is advanced with respect to video"
		::= { htg3001c01v1Entry 247 }

		-- 1.3.6.1.4.1.10106.3.101291.1.1.249
		htg3001c01v1DelayG3p1r OBJECT-TYPE
			SYNTAX DelayX1Ms
			MAX-ACCESS read-only
			STATUS current
			DESCRIPTION
				"A negative value implies that audio is advanced with respect to video"
		::= { htg3001c01v1Entry 249 }

		-- 1.3.6.1.4.1.10106.3.101291.1.1.251
		htg3001c01v1DelayG4p0l OBJECT-TYPE
			SYNTAX DelayX1Ms
			MAX-ACCESS read-only
			STATUS current
			DESCRIPTION
				"A negative value implies that audio is advanced with respect to video"
		::= { htg3001c01v1Entry 251 }

		-- 1.3.6.1.4.1.10106.3.101291.1.1.253
		htg3001c01v1DelayG4p0r OBJECT-TYPE
			SYNTAX DelayX1Ms
			MAX-ACCESS read-only
			STATUS current
			DESCRIPTION
				"A negative value implies that audio is advanced with respect to video"
		::= { htg3001c01v1Entry 253 }

		-- 1.3.6.1.4.1.10106.3.101291.1.1.255
		htg3001c01v1DelayG4p1l OBJECT-TYPE
			SYNTAX DelayX1Ms
			MAX-ACCESS read-only
			STATUS current
			DESCRIPTION
				"A negative value implies that audio is advanced with respect to video"
		::= { htg3001c01v1Entry 255 }

		-- 1.3.6.1.4.1.10106.3.101291.1.1.257
		htg3001c01v1DelayG4p1r OBJECT-TYPE
			SYNTAX DelayX1Ms
			MAX-ACCESS read-only
			STATUS current
			DESCRIPTION
				"A negative value implies that audio is advanced with respect to video"
		::= { htg3001c01v1Entry 257 }

		-- 1.3.6.1.4.1.10106.3.101291.1.1.259
		htg3001c01v1AvSeqG1p0 OBJECT-TYPE
			SYNTAX BitFail
			MAX-ACCESS read-only
			STATUS current
			DESCRIPTION
				"The A/V delay measurement sequence was not correctly detected for this pair"
		::= { htg3001c01v1Entry 259 }

		-- 1.3.6.1.4.1.10106.3.101291.1.1.261
		htg3001c01v1AvSeqG1p1 OBJECT-TYPE
			SYNTAX BitFail
			MAX-ACCESS read-only
			STATUS current
			DESCRIPTION
				"The A/V delay measurement sequence was not correctly detected for this pair"
		::= { htg3001c01v1Entry 261 }

		-- 1.3.6.1.4.1.10106.3.101291.1.1.263
		htg3001c01v1AvSeqG2p0 OBJECT-TYPE
			SYNTAX BitFail
			MAX-ACCESS read-only
			STATUS current
			DESCRIPTION
				"The A/V delay measurement sequence was not correctly detected for this pair"
		::= { htg3001c01v1Entry 263 }

		-- 1.3.6.1.4.1.10106.3.101291.1.1.265
		htg3001c01v1AvSeqG2p1 OBJECT-TYPE
			SYNTAX BitFail
			MAX-ACCESS read-only
			STATUS current
			DESCRIPTION
				"The A/V delay measurement sequence was not correctly detected for this pair"
		::= { htg3001c01v1Entry 265 }

		-- 1.3.6.1.4.1.10106.3.101291.1.1.267
		htg3001c01v1AvSeqG3p0 OBJECT-TYPE
			SYNTAX BitFail
			MAX-ACCESS read-only
			STATUS current
			DESCRIPTION
				"The A/V delay measurement sequence was not correctly detected for this pair"
		::= { htg3001c01v1Entry 267 }

		-- 1.3.6.1.4.1.10106.3.101291.1.1.269
		htg3001c01v1AvSeqG3p1 OBJECT-TYPE
			SYNTAX BitFail
			MAX-ACCESS read-only
			STATUS current
			DESCRIPTION
				"The A/V delay measurement sequence was not correctly detected for this pair"
		::= { htg3001c01v1Entry 269 }

		-- 1.3.6.1.4.1.10106.3.101291.1.1.271
		htg3001c01v1AvSeqG4p0 OBJECT-TYPE
			SYNTAX BitFail
			MAX-ACCESS read-only
			STATUS current
			DESCRIPTION
				"The A/V delay measurement sequence was not correctly detected for this pair"
		::= { htg3001c01v1Entry 271 }

		-- 1.3.6.1.4.1.10106.3.101291.1.1.273
		htg3001c01v1AvSeqG4p1 OBJECT-TYPE
			SYNTAX BitFail
			MAX-ACCESS read-only
			STATUS current
			DESCRIPTION
				"The A/V delay measurement sequence was not correctly detected for this pair"
		::= { htg3001c01v1Entry 273 }

		-- 1.3.6.1.4.1.10106.3.101291.1.1.275
		htg3001c01v1AudGrpPres1 OBJECT-TYPE
			SYNTAX BitFailN
			MAX-ACCESS read-only
			STATUS current
			DESCRIPTION
				"Group 1 present"
		::= { htg3001c01v1Entry 275 }

		-- 1.3.6.1.4.1.10106.3.101291.1.1.277
		htg3001c01v1AudGrpPres2 OBJECT-TYPE
			SYNTAX BitFailN
			MAX-ACCESS read-only
			STATUS current
			DESCRIPTION
				"Group 2 present"
		::= { htg3001c01v1Entry 277 }

		-- 1.3.6.1.4.1.10106.3.101291.1.1.279
		htg3001c01v1AudGrpPres3 OBJECT-TYPE
			SYNTAX BitFailN
			MAX-ACCESS read-only
			STATUS current
			DESCRIPTION
				"Group 3 present"
		::= { htg3001c01v1Entry 279 }

		-- 1.3.6.1.4.1.10106.3.101291.1.1.281
		htg3001c01v1AudGrpPres4 OBJECT-TYPE
			SYNTAX BitFailN
			MAX-ACCESS read-only
			STATUS current
			DESCRIPTION
				"Group 4 present"
		::= { htg3001c01v1Entry 281 }

		-- 1.3.6.1.4.1.10106.3.101291.1.1.283
		htg3001c01v1AvSeqPhase OBJECT-TYPE
			SYNTAX Uint8
			MAX-ACCESS read-only
			STATUS current
			DESCRIPTION
				"Seconds remaining until next delay measurement sequence starts"
		::= { htg3001c01v1Entry 283 }

		-- 1.3.6.1.4.1.10106.3.494401
		psu3300c03v1 OBJECT IDENTIFIER ::= { albalaProducts 494401 }

		-- 1.3.6.1.4.1.10106.3.494401.1
		psu3300c03v1Table  OBJECT-TYPE
			SYNTAX SEQUENCE OF Psu3300c03v1Entry
			MAX-ACCESS not-accessible
			STATUS current
			DESCRIPTION
				"Module  PSU3300C03V1 Table"
			::= { psu3300c03v1 1 }

		-- 1.3.6.1.4.1.10106.3.494401.1.1
		psu3300c03v1Entry  OBJECT-TYPE
			SYNTAX Psu3300c03v1Entry
			MAX-ACCESS not-accessible
			STATUS current
			DESCRIPTION
				"Module PSU3300C03V1 Entry"
			INDEX { psu3300c03v1Index }
			::= { psu3300c03v1Table 1 }

			Psu3300c03v1Entry ::=
			SEQUENCE {
				psu3300c03v1Index
				ModuleIndex,
				psu3300c03v1PowerOff
				BitFail,
				psu3300c03v1PowerOffTrapEnable
				AlarmEnable,
				psu3300c03v1TempWarning
				BitFail,
				psu3300c03v1TempWarningTrapEnable
				AlarmEnable,
				psu3300c03v1TempFail
				BitFail,
				psu3300c03v1TempFailTrapEnable
				AlarmEnable,
				psu3300c03v1ActTemp
				Temperature0c1,
				psu3300c03v1MeanTemp
				Temperature0c1,
				psu3300c03v1MaxTemp
				Temperature0c1,
				psu3300c03v1PonHours
				Uint16,
				psu3300c03v1TotMaxTemp
				Temperature0c1,
				psu3300c03v1TotPonHours
				Uint16,
				psu3300c03v1TotPonTimes
				Uint16,
				psu3300c03v1SerialNo
				SerialNo,
				psu3300c03v1InputVolt
				PsuDcInpV
			 }

		-- 1.3.6.1.4.1.10106.3.101291.1.1.1
		psu3300c03v1Index OBJECT-TYPE
			SYNTAX ModuleIndex
			MAX-ACCESS read-only
			STATUS current
			DESCRIPTION
				"Index of PSU3300C03V1 Table"
		::= { psu3300c03v1Entry 1 }

		-- 1.3.6.1.4.1.10106.3.101291.1.1.3
		psu3300c03v1PowerOff OBJECT-TYPE
			SYNTAX BitFail
			MAX-ACCESS read-only
			STATUS current
			DESCRIPTION
				"Indicates the power supply status"
		::= { psu3300c03v1Entry 3 }

		-- 1.3.6.1.4.1.10106.3.101291.1.1.4
		psu3300c03v1PowerOffTrapEnable OBJECT-TYPE
			SYNTAX AlarmEnable
			MAX-ACCESS read-write
			STATUS current
			DESCRIPTION
				"Indicates the power supply status Trap Enable"
		::= { psu3300c03v1Entry 4 }

		-- 1.3.6.1.4.1.10106.3.101291.1.1.5
		psu3300c03v1TempWarning OBJECT-TYPE
			SYNTAX BitFail
			MAX-ACCESS read-only
			STATUS current
			DESCRIPTION
				"Indicates that actual temperature is over expected range"
		::= { psu3300c03v1Entry 5 }

		-- 1.3.6.1.4.1.10106.3.101291.1.1.6
		psu3300c03v1TempWarningTrapEnable OBJECT-TYPE
			SYNTAX AlarmEnable
			MAX-ACCESS read-write
			STATUS current
			DESCRIPTION
				"Indicates that actual temperature is over expected range Trap Enable"
		::= { psu3300c03v1Entry 6 }

		-- 1.3.6.1.4.1.10106.3.101291.1.1.7
		psu3300c03v1TempFail OBJECT-TYPE
			SYNTAX BitFail
			MAX-ACCESS read-only
			STATUS current
			DESCRIPTION
				"Indicates that actual temperature is over recommended range"
		::= { psu3300c03v1Entry 7 }

		-- 1.3.6.1.4.1.10106.3.101291.1.1.8
		psu3300c03v1TempFailTrapEnable OBJECT-TYPE
			SYNTAX AlarmEnable
			MAX-ACCESS read-write
			STATUS current
			DESCRIPTION
				"Indicates that actual temperature is over recommended range Trap Enable"
		::= { psu3300c03v1Entry 8 }

		-- 1.3.6.1.4.1.10106.3.101291.1.1.9
		psu3300c03v1ActTemp OBJECT-TYPE
			SYNTAX Temperature0c1
			MAX-ACCESS read-only
			STATUS current
			DESCRIPTION
				"Displays internal actual temperature"
		::= { psu3300c03v1Entry 9 }

		-- 1.3.6.1.4.1.10106.3.101291.1.1.11
		psu3300c03v1MeanTemp OBJECT-TYPE
			SYNTAX Temperature0c1
			MAX-ACCESS read-only
			STATUS current
			DESCRIPTION
				"Displays internal mean temperature"
		::= { psu3300c03v1Entry 11 }

		-- 1.3.6.1.4.1.10106.3.101291.1.1.13
		psu3300c03v1MaxTemp OBJECT-TYPE
			SYNTAX Temperature0c1
			MAX-ACCESS read-only
			STATUS current
			DESCRIPTION
				"Displays internal maximum temperature"
		::= { psu3300c03v1Entry 13 }

		-- 1.3.6.1.4.1.10106.3.101291.1.1.15
		psu3300c03v1PonHours OBJECT-TYPE
			SYNTAX Uint16
			MAX-ACCESS read-only
			STATUS current
			DESCRIPTION
				"Displays module power on time"
		::= { psu3300c03v1Entry 15 }

		-- 1.3.6.1.4.1.10106.3.101291.1.1.17
		psu3300c03v1TotMaxTemp OBJECT-TYPE
			SYNTAX Temperature0c1
			MAX-ACCESS read-only
			STATUS current
			DESCRIPTION
				"Displays internal maximum tempertature since first power on"
		::= { psu3300c03v1Entry 17 }

		-- 1.3.6.1.4.1.10106.3.101291.1.1.19
		psu3300c03v1TotPonHours OBJECT-TYPE
			SYNTAX Uint16
			MAX-ACCESS read-only
			STATUS current
			DESCRIPTION
				"Displays module power on time since first power on"
		::= { psu3300c03v1Entry 19 }

		-- 1.3.6.1.4.1.10106.3.101291.1.1.21
		psu3300c03v1TotPonTimes OBJECT-TYPE
			SYNTAX Uint16
			MAX-ACCESS read-only
			STATUS current
			DESCRIPTION
				"Displays module power on events since first power on"
		::= { psu3300c03v1Entry 21 }

		-- 1.3.6.1.4.1.10106.3.101291.1.1.23
		psu3300c03v1SerialNo OBJECT-TYPE
			SYNTAX SerialNo
			MAX-ACCESS read-only
			STATUS current
			DESCRIPTION
				"Serial number"
		::= { psu3300c03v1Entry 23 }

		-- 1.3.6.1.4.1.10106.3.101291.1.1.25
		psu3300c03v1InputVolt OBJECT-TYPE
			SYNTAX PsuDcInpV
			MAX-ACCESS read-only
			STATUS current
			DESCRIPTION
				"Displays the DC input voltaje"
		::= { psu3300c03v1Entry 25 }

		-- 1.3.6.1.4.1.10106.3.496001
		ttd3000c03v1 OBJECT IDENTIFIER ::= { albalaProducts 496001 }

		-- 1.3.6.1.4.1.10106.3.496001.1
		ttd3000c03v1Table  OBJECT-TYPE
			SYNTAX SEQUENCE OF Ttd3000c03v1Entry
			MAX-ACCESS not-accessible
			STATUS current
			DESCRIPTION
				"Module  TTD3000C03V1 Table"
			::= { ttd3000c03v1 1 }

		-- 1.3.6.1.4.1.10106.3.496001.1.1
		ttd3000c03v1Entry  OBJECT-TYPE
			SYNTAX Ttd3000c03v1Entry
			MAX-ACCESS not-accessible
			STATUS current
			DESCRIPTION
				"Module TTD3000C03V1 Entry"
			INDEX { ttd3000c03v1Index }
			::= { ttd3000c03v1Table 1 }

			Ttd3000c03v1Entry ::=
			SEQUENCE {
				ttd3000c03v1Index
				ModuleIndex,
				ttd3000c03v1Mode
				ChgOverMode2,
				ttd3000c03v1ModeTrapEnable
				AlarmEnable,
				ttd3000c03v1InputA
				TtdInput,
				ttd3000c03v1InputATrapEnable
				AlarmEnable,
				ttd3000c03v1InputB
				TtdInput,
				ttd3000c03v1InputBTrapEnable
				AlarmEnable,
				ttd3000c03v1Impedance
				Impedance,
				ttd3000c03v1FreqRange
				FreqRange,
				ttd3000c03v1ExpectedFreq
				TtdFreq,
				ttd3000c03v1FreqFailOffset
				TtdFreq,
				ttd3000c03v1InputALvFail
				BitFail,
				ttd3000c03v1InputALvFailTrapEnable
				AlarmEnable,
				ttd3000c03v1InputAFrFail
				BitFail,
				ttd3000c03v1InputAFrFailTrapEnable
				AlarmEnable,
				ttd3000c03v1InputBLbFail
				BitFail,
				ttd3000c03v1InputBLbFailTrapEnable
				AlarmEnable,
				ttd3000c03v1InputBFrFail
				BitFail,
				ttd3000c03v1InputBFrFailTrapEnable
				AlarmEnable,
				ttd3000c03v1FreqA
				TtdFreq,
				ttd3000c03v1FreqB
				TtdFreq,
				ttd3000c03v1SerialNo
				SerialNo
			 }

		-- 1.3.6.1.4.1.10106.3.101291.1.1.1
		ttd3000c03v1Index OBJECT-TYPE
			SYNTAX ModuleIndex
			MAX-ACCESS read-only
			STATUS current
			DESCRIPTION
				"Index of TTD3000C03V1 Table"
		::= { ttd3000c03v1Entry 1 }

		-- 1.3.6.1.4.1.10106.3.101291.1.1.3
		ttd3000c03v1Mode OBJECT-TYPE
			SYNTAX ChgOverMode2
			MAX-ACCESS read-write
			STATUS current
			DESCRIPTION
				"Allows selecting the switching mode"
		::= { ttd3000c03v1Entry 3 }

		-- 1.3.6.1.4.1.10106.3.101291.1.1.4
		ttd3000c03v1ModeTrapEnable OBJECT-TYPE
			SYNTAX AlarmEnable
			MAX-ACCESS read-write
			STATUS current
			DESCRIPTION
				"Allows selecting the switching mode Trap Enable"
		::= { ttd3000c03v1Entry 4 }

		-- 1.3.6.1.4.1.10106.3.101291.1.1.5
		ttd3000c03v1InputA OBJECT-TYPE
			SYNTAX TtdInput
			MAX-ACCESS read-write
			STATUS current
			DESCRIPTION
				"Selected input"
		::= { ttd3000c03v1Entry 5 }

		-- 1.3.6.1.4.1.10106.3.101291.1.1.6
		ttd3000c03v1InputATrapEnable OBJECT-TYPE
			SYNTAX AlarmEnable
			MAX-ACCESS read-write
			STATUS current
			DESCRIPTION
				"Selected input Trap Enable"
		::= { ttd3000c03v1Entry 6 }

		-- 1.3.6.1.4.1.10106.3.101291.1.1.7
		ttd3000c03v1InputB OBJECT-TYPE
			SYNTAX TtdInput
			MAX-ACCESS read-write
			STATUS current
			DESCRIPTION
				"Selected input"
		::= { ttd3000c03v1Entry 7 }

		-- 1.3.6.1.4.1.10106.3.101291.1.1.8
		ttd3000c03v1InputBTrapEnable OBJECT-TYPE
			SYNTAX AlarmEnable
			MAX-ACCESS read-write
			STATUS current
			DESCRIPTION
				"Selected input Trap Enable"
		::= { ttd3000c03v1Entry 8 }

		-- 1.3.6.1.4.1.10106.3.101291.1.1.9
		ttd3000c03v1Impedance OBJECT-TYPE
			SYNTAX Impedance
			MAX-ACCESS read-write
			STATUS current
			DESCRIPTION
				"Allows selecting the output impedance"
		::= { ttd3000c03v1Entry 9 }

		-- 1.3.6.1.4.1.10106.3.101291.1.1.11
		ttd3000c03v1FreqRange OBJECT-TYPE
			SYNTAX FreqRange
			MAX-ACCESS read-write
			STATUS current
			DESCRIPTION
				"Allows selecting the frequency measure range"
		::= { ttd3000c03v1Entry 11 }

		-- 1.3.6.1.4.1.10106.3.101291.1.1.13
		ttd3000c03v1ExpectedFreq OBJECT-TYPE
			SYNTAX TtdFreq
			MAX-ACCESS read-write
			STATUS current
			DESCRIPTION
				"Allows selecting the expected frequency"
		::= { ttd3000c03v1Entry 13 }

		-- 1.3.6.1.4.1.10106.3.101291.1.1.15
		ttd3000c03v1FreqFailOffset OBJECT-TYPE
			SYNTAX TtdFreq
			MAX-ACCESS read-write
			STATUS current
			DESCRIPTION
				"Allows selecting the frequency offset that causes fail"
		::= { ttd3000c03v1Entry 15 }

		-- 1.3.6.1.4.1.10106.3.101291.1.1.17
		ttd3000c03v1InputALvFail OBJECT-TYPE
			SYNTAX BitFail
			MAX-ACCESS read-only
			STATUS current
			DESCRIPTION
				"Indicates signal presence fail"
		::= { ttd3000c03v1Entry 17 }

		-- 1.3.6.1.4.1.10106.3.101291.1.1.18
		ttd3000c03v1InputALvFailTrapEnable OBJECT-TYPE
			SYNTAX AlarmEnable
			MAX-ACCESS read-write
			STATUS current
			DESCRIPTION
				"Indicates signal presence fail Trap Enable"
		::= { ttd3000c03v1Entry 18 }

		-- 1.3.6.1.4.1.10106.3.101291.1.1.19
		ttd3000c03v1InputAFrFail OBJECT-TYPE
			SYNTAX BitFail
			MAX-ACCESS read-only
			STATUS current
			DESCRIPTION
				"Indicates signal frequency fail"
		::= { ttd3000c03v1Entry 19 }

		-- 1.3.6.1.4.1.10106.3.101291.1.1.20
		ttd3000c03v1InputAFrFailTrapEnable OBJECT-TYPE
			SYNTAX AlarmEnable
			MAX-ACCESS read-write
			STATUS current
			DESCRIPTION
				"Indicates signal frequency fail Trap Enable"
		::= { ttd3000c03v1Entry 20 }

		-- 1.3.6.1.4.1.10106.3.101291.1.1.21
		ttd3000c03v1InputBLbFail OBJECT-TYPE
			SYNTAX BitFail
			MAX-ACCESS read-only
			STATUS current
			DESCRIPTION
				"Indicates signal presence fail"
		::= { ttd3000c03v1Entry 21 }

		-- 1.3.6.1.4.1.10106.3.101291.1.1.22
		ttd3000c03v1InputBLbFailTrapEnable OBJECT-TYPE
			SYNTAX AlarmEnable
			MAX-ACCESS read-write
			STATUS current
			DESCRIPTION
				"Indicates signal presence fail Trap Enable"
		::= { ttd3000c03v1Entry 22 }

		-- 1.3.6.1.4.1.10106.3.101291.1.1.23
		ttd3000c03v1InputBFrFail OBJECT-TYPE
			SYNTAX BitFail
			MAX-ACCESS read-only
			STATUS current
			DESCRIPTION
				"Indicates signal frequency fail"
		::= { ttd3000c03v1Entry 23 }

		-- 1.3.6.1.4.1.10106.3.101291.1.1.24
		ttd3000c03v1InputBFrFailTrapEnable OBJECT-TYPE
			SYNTAX AlarmEnable
			MAX-ACCESS read-write
			STATUS current
			DESCRIPTION
				"Indicates signal frequency fail Trap Enable"
		::= { ttd3000c03v1Entry 24 }

		-- 1.3.6.1.4.1.10106.3.101291.1.1.25
		ttd3000c03v1FreqA OBJECT-TYPE
			SYNTAX TtdFreq
			MAX-ACCESS read-only
			STATUS current
			DESCRIPTION
				"Indicates the signal frequency"
		::= { ttd3000c03v1Entry 25 }

		-- 1.3.6.1.4.1.10106.3.101291.1.1.27
		ttd3000c03v1FreqB OBJECT-TYPE
			SYNTAX TtdFreq
			MAX-ACCESS read-only
			STATUS current
			DESCRIPTION
				"Indicates the signal frequency"
		::= { ttd3000c03v1Entry 27 }

		-- 1.3.6.1.4.1.10106.3.101291.1.1.29
		ttd3000c03v1SerialNo OBJECT-TYPE
			SYNTAX SerialNo
			MAX-ACCESS read-only
			STATUS current
			DESCRIPTION
				"Serial number"
		::= { ttd3000c03v1Entry 29 }

		-- 1.3.6.1.4.1.10106.3.497501
		adb2008c01v1 OBJECT IDENTIFIER ::= { albalaProducts 497501 }

		-- 1.3.6.1.4.1.10106.3.497501.1
		adb2008c01v1Table  OBJECT-TYPE
			SYNTAX SEQUENCE OF Adb2008c01v1Entry
			MAX-ACCESS not-accessible
			STATUS current
			DESCRIPTION
				"Module  ADB2008C01V1 Table"
			::= { adb2008c01v1 1 }

		-- 1.3.6.1.4.1.10106.3.497501.1.1
		adb2008c01v1Entry  OBJECT-TYPE
			SYNTAX Adb2008c01v1Entry
			MAX-ACCESS not-accessible
			STATUS current
			DESCRIPTION
				"Module ADB2008C01V1 Entry"
			INDEX { adb2008c01v1Index }
			::= { adb2008c01v1Table 1 }

			Adb2008c01v1Entry ::=
			SEQUENCE {
				adb2008c01v1Index
				ModuleIndex,
				adb2008c01v1ActivePreset
				Preset16Active,
				adb2008c01v1LoadPreset
				Preset16Load,
				adb2008c01v1SavePreset
				Preset16Save,
				adb2008c01v1ManNAuto
				Bit0Aut1Man,
				adb2008c01v1BaseSlot
				Uint5,
				adb2008c01v1SlotUsed
				AdbDabSlot,
				adb2008c01v1OvldLevel
				LevelDbfsA,
				adb2008c01v1Gain0
				Gain24dbMute,
				adb2008c01v1Phase0
				Bit0Nor1Inv,
				adb2008c01v1Gain1
				Gain24dbMute,
				adb2008c01v1Phase1
				Bit0Nor1Inv,
				adb2008c01v1Gain2
				Gain24dbMute,
				adb2008c01v1Phase2
				Bit0Nor1Inv,
				adb2008c01v1Gain3
				Gain24dbMute,
				adb2008c01v1Phase3
				Bit0Nor1Inv,
				adb2008c01v1Gain4
				Gain24dbMute,
				adb2008c01v1Phase4
				Bit0Nor1Inv,
				adb2008c01v1Gain5
				Gain24dbMute,
				adb2008c01v1Phase5
				Bit0Nor1Inv,
				adb2008c01v1Gain6
				Gain24dbMute,
				adb2008c01v1Phase6
				Bit0Nor1Inv,
				adb2008c01v1Gain7
				Gain24dbMute,
				adb2008c01v1Phase7
				Bit0Nor1Inv,
				adb2008c01v1BusTimFail
				BitFail,
				adb2008c01v1BusTimFailTrapEnable
				AlarmEnable,
				adb2008c01v1BusTimUnlck
				BitFail,
				adb2008c01v1BusTimUnlckTrapEnable
				AlarmEnable,
				adb2008c01v1BusAudFail
				BitFail,
				adb2008c01v1BusAudFailTrapEnable
				AlarmEnable,
				adb2008c01v1BusAudError
				BitFail,
				adb2008c01v1BusAudErrorTrapEnable
				AlarmEnable,
				adb2008c01v1AudClipEr
				BitFail,
				adb2008c01v1AudClipErTrapEnable
				AlarmEnable,
				adb2008c01v1AudInsFail
				BitFail,
				adb2008c01v1AudInsFailTrapEnable
				AlarmEnable,
				adb2008c01v1AudOvldFail
				BitFail,
				adb2008c01v1AudOvldFailTrapEnable
				AlarmEnable,
				adb2008c01v1Slot1Pres
				Bit0No1Yes,
				adb2008c01v1Slot2Pres
				Bit0No1Yes,
				adb2008c01v1Slot3Pres
				Bit0No1Yes,
				adb2008c01v1Slot4Pres
				Bit0No1Yes,
				adb2008c01v1Slot5Pres
				Bit0No1Yes,
				adb2008c01v1Slot6Pres
				Bit0No1Yes,
				adb2008c01v1Slot7Pres
				Bit0No1Yes,
				adb2008c01v1Slot8Pres
				Bit0No1Yes,
				adb2008c01v1SerialNo
				SerialNo
			 }

		-- 1.3.6.1.4.1.10106.3.101291.1.1.1
		adb2008c01v1Index OBJECT-TYPE
			SYNTAX ModuleIndex
			MAX-ACCESS read-only
			STATUS current
			DESCRIPTION
				"Index of ADB2008C01V1 Table"
		::= { adb2008c01v1Entry 1 }

		-- 1.3.6.1.4.1.10106.3.101291.1.1.3
		adb2008c01v1ActivePreset OBJECT-TYPE
			SYNTAX Preset16Active
			MAX-ACCESS read-only
			STATUS current
			DESCRIPTION
				"Shows the active preset"
		::= { adb2008c01v1Entry 3 }

		-- 1.3.6.1.4.1.10106.3.101291.1.1.5
		adb2008c01v1LoadPreset OBJECT-TYPE
			SYNTAX Preset16Load
			MAX-ACCESS read-write
			STATUS current
			DESCRIPTION
				"Allows loading a preset"
		::= { adb2008c01v1Entry 5 }

		-- 1.3.6.1.4.1.10106.3.101291.1.1.7
		adb2008c01v1SavePreset OBJECT-TYPE
			SYNTAX Preset16Save
			MAX-ACCESS read-write
			STATUS current
			DESCRIPTION
				"Allows saving a preset"
		::= { adb2008c01v1Entry 7 }

		-- 1.3.6.1.4.1.10106.3.101291.1.1.9
		adb2008c01v1ManNAuto OBJECT-TYPE
			SYNTAX Bit0Aut1Man
			MAX-ACCESS read-write
			STATUS current
			DESCRIPTION
				"It allows selecting the slot working mode"
		::= { adb2008c01v1Entry 9 }

		-- 1.3.6.1.4.1.10106.3.101291.1.1.11
		adb2008c01v1BaseSlot OBJECT-TYPE
			SYNTAX Uint5
			MAX-ACCESS read-write
			STATUS current
			DESCRIPTION
				"Base rack slot"
		::= { adb2008c01v1Entry 11 }

		-- 1.3.6.1.4.1.10106.3.101291.1.1.13
		adb2008c01v1SlotUsed OBJECT-TYPE
			SYNTAX AdbDabSlot
			MAX-ACCESS read-write
			STATUS current
			DESCRIPTION
				"Employed slot (insertion)"
		::= { adb2008c01v1Entry 13 }

		-- 1.3.6.1.4.1.10106.3.101291.1.1.15
		adb2008c01v1OvldLevel OBJECT-TYPE
			SYNTAX LevelDbfsA
			MAX-ACCESS read-write
			STATUS current
			DESCRIPTION
				"It allows selecting the overload audio level"
		::= { adb2008c01v1Entry 15 }

		-- 1.3.6.1.4.1.10106.3.101291.1.1.17
		adb2008c01v1Gain0 OBJECT-TYPE
			SYNTAX Gain24dbMute
			MAX-ACCESS read-write
			STATUS current
			DESCRIPTION
				"Gain applied to the analogue input 1"
		::= { adb2008c01v1Entry 17 }

		-- 1.3.6.1.4.1.10106.3.101291.1.1.19
		adb2008c01v1Phase0 OBJECT-TYPE
			SYNTAX Bit0Nor1Inv
			MAX-ACCESS read-write
			STATUS current
			DESCRIPTION
				"Phase gain applied to the analogue audio input 1"
		::= { adb2008c01v1Entry 19 }

		-- 1.3.6.1.4.1.10106.3.101291.1.1.21
		adb2008c01v1Gain1 OBJECT-TYPE
			SYNTAX Gain24dbMute
			MAX-ACCESS read-write
			STATUS current
			DESCRIPTION
				"Gain applied to the analogue input 2"
		::= { adb2008c01v1Entry 21 }

		-- 1.3.6.1.4.1.10106.3.101291.1.1.23
		adb2008c01v1Phase1 OBJECT-TYPE
			SYNTAX Bit0Nor1Inv
			MAX-ACCESS read-write
			STATUS current
			DESCRIPTION
				"Phase gain applied to the analogue audio input 2"
		::= { adb2008c01v1Entry 23 }

		-- 1.3.6.1.4.1.10106.3.101291.1.1.25
		adb2008c01v1Gain2 OBJECT-TYPE
			SYNTAX Gain24dbMute
			MAX-ACCESS read-write
			STATUS current
			DESCRIPTION
				"Gain applied to the analogue input 3"
		::= { adb2008c01v1Entry 25 }

		-- 1.3.6.1.4.1.10106.3.101291.1.1.27
		adb2008c01v1Phase2 OBJECT-TYPE
			SYNTAX Bit0Nor1Inv
			MAX-ACCESS read-write
			STATUS current
			DESCRIPTION
				"Phase gain applied to the analogue audio input 3"
		::= { adb2008c01v1Entry 27 }

		-- 1.3.6.1.4.1.10106.3.101291.1.1.29
		adb2008c01v1Gain3 OBJECT-TYPE
			SYNTAX Gain24dbMute
			MAX-ACCESS read-write
			STATUS current
			DESCRIPTION
				"Gain applied to the analogue input 4"
		::= { adb2008c01v1Entry 29 }

		-- 1.3.6.1.4.1.10106.3.101291.1.1.31
		adb2008c01v1Phase3 OBJECT-TYPE
			SYNTAX Bit0Nor1Inv
			MAX-ACCESS read-write
			STATUS current
			DESCRIPTION
				"Phase gain applied to the analogue audio input 4"
		::= { adb2008c01v1Entry 31 }

		-- 1.3.6.1.4.1.10106.3.101291.1.1.33
		adb2008c01v1Gain4 OBJECT-TYPE
			SYNTAX Gain24dbMute
			MAX-ACCESS read-write
			STATUS current
			DESCRIPTION
				"Gain applied to the analogue input 5"
		::= { adb2008c01v1Entry 33 }

		-- 1.3.6.1.4.1.10106.3.101291.1.1.35
		adb2008c01v1Phase4 OBJECT-TYPE
			SYNTAX Bit0Nor1Inv
			MAX-ACCESS read-write
			STATUS current
			DESCRIPTION
				"Phase gain applied to the analogue audio input 5"
		::= { adb2008c01v1Entry 35 }

		-- 1.3.6.1.4.1.10106.3.101291.1.1.37
		adb2008c01v1Gain5 OBJECT-TYPE
			SYNTAX Gain24dbMute
			MAX-ACCESS read-write
			STATUS current
			DESCRIPTION
				"Gain applied to the analogue input 6"
		::= { adb2008c01v1Entry 37 }

		-- 1.3.6.1.4.1.10106.3.101291.1.1.39
		adb2008c01v1Phase5 OBJECT-TYPE
			SYNTAX Bit0Nor1Inv
			MAX-ACCESS read-write
			STATUS current
			DESCRIPTION
				"Phase gain applied to the analogue audio input 6"
		::= { adb2008c01v1Entry 39 }

		-- 1.3.6.1.4.1.10106.3.101291.1.1.41
		adb2008c01v1Gain6 OBJECT-TYPE
			SYNTAX Gain24dbMute
			MAX-ACCESS read-write
			STATUS current
			DESCRIPTION
				"Gain applied to the analogue input 7"
		::= { adb2008c01v1Entry 41 }

		-- 1.3.6.1.4.1.10106.3.101291.1.1.43
		adb2008c01v1Phase6 OBJECT-TYPE
			SYNTAX Bit0Nor1Inv
			MAX-ACCESS read-write
			STATUS current
			DESCRIPTION
				"Phase gain applied to the analogue audio input 7"
		::= { adb2008c01v1Entry 43 }

		-- 1.3.6.1.4.1.10106.3.101291.1.1.45
		adb2008c01v1Gain7 OBJECT-TYPE
			SYNTAX Gain24dbMute
			MAX-ACCESS read-write
			STATUS current
			DESCRIPTION
				"Gain applied to the analogue input 8"
		::= { adb2008c01v1Entry 45 }

		-- 1.3.6.1.4.1.10106.3.101291.1.1.47
		adb2008c01v1Phase7 OBJECT-TYPE
			SYNTAX Bit0Nor1Inv
			MAX-ACCESS read-write
			STATUS current
			DESCRIPTION
				"Phase gain applied to the analogue audio input 8"
		::= { adb2008c01v1Entry 47 }

		-- 1.3.6.1.4.1.10106.3.101291.1.1.49
		adb2008c01v1BusTimFail OBJECT-TYPE
			SYNTAX BitFail
			MAX-ACCESS read-only
			STATUS current
			DESCRIPTION
				"Synchronization internal rack bus fail"
		::= { adb2008c01v1Entry 49 }

		-- 1.3.6.1.4.1.10106.3.101291.1.1.50
		adb2008c01v1BusTimFailTrapEnable OBJECT-TYPE
			SYNTAX AlarmEnable
			MAX-ACCESS read-write
			STATUS current
			DESCRIPTION
				"Synchronization internal rack bus fail Trap Enable"
		::= { adb2008c01v1Entry 50 }

		-- 1.3.6.1.4.1.10106.3.101291.1.1.51
		adb2008c01v1BusTimUnlck OBJECT-TYPE
			SYNTAX BitFail
			MAX-ACCESS read-only
			STATUS current
			DESCRIPTION
				"Synchronization internal rack bus unlocked"
		::= { adb2008c01v1Entry 51 }

		-- 1.3.6.1.4.1.10106.3.101291.1.1.52
		adb2008c01v1BusTimUnlckTrapEnable OBJECT-TYPE
			SYNTAX AlarmEnable
			MAX-ACCESS read-write
			STATUS current
			DESCRIPTION
				"Synchronization internal rack bus unlocked Trap Enable"
		::= { adb2008c01v1Entry 52 }

		-- 1.3.6.1.4.1.10106.3.101291.1.1.53
		adb2008c01v1BusAudFail OBJECT-TYPE
			SYNTAX BitFail
			MAX-ACCESS read-only
			STATUS current
			DESCRIPTION
				"Audio bus fail"
		::= { adb2008c01v1Entry 53 }

		-- 1.3.6.1.4.1.10106.3.101291.1.1.54
		adb2008c01v1BusAudFailTrapEnable OBJECT-TYPE
			SYNTAX AlarmEnable
			MAX-ACCESS read-write
			STATUS current
			DESCRIPTION
				"Audio bus fail Trap Enable"
		::= { adb2008c01v1Entry 54 }

		-- 1.3.6.1.4.1.10106.3.101291.1.1.55
		adb2008c01v1BusAudError OBJECT-TYPE
			SYNTAX BitFail
			MAX-ACCESS read-only
			STATUS current
			DESCRIPTION
				"Audio bus errors"
		::= { adb2008c01v1Entry 55 }

		-- 1.3.6.1.4.1.10106.3.101291.1.1.56
		adb2008c01v1BusAudErrorTrapEnable OBJECT-TYPE
			SYNTAX AlarmEnable
			MAX-ACCESS read-write
			STATUS current
			DESCRIPTION
				"Audio bus errors Trap Enable"
		::= { adb2008c01v1Entry 56 }

		-- 1.3.6.1.4.1.10106.3.101291.1.1.57
		adb2008c01v1AudClipEr OBJECT-TYPE
			SYNTAX BitFail
			MAX-ACCESS read-only
			STATUS current
			DESCRIPTION
				"Audio clipping error"
		::= { adb2008c01v1Entry 57 }

		-- 1.3.6.1.4.1.10106.3.101291.1.1.58
		adb2008c01v1AudClipErTrapEnable OBJECT-TYPE
			SYNTAX AlarmEnable
			MAX-ACCESS read-write
			STATUS current
			DESCRIPTION
				"Audio clipping error Trap Enable"
		::= { adb2008c01v1Entry 58 }

		-- 1.3.6.1.4.1.10106.3.101291.1.1.59
		adb2008c01v1AudInsFail OBJECT-TYPE
			SYNTAX BitFail
			MAX-ACCESS read-only
			STATUS current
			DESCRIPTION
				"It lights up when the module cannot insert in the backplane bus the audio channels"
		::= { adb2008c01v1Entry 59 }

		-- 1.3.6.1.4.1.10106.3.101291.1.1.60
		adb2008c01v1AudInsFailTrapEnable OBJECT-TYPE
			SYNTAX AlarmEnable
			MAX-ACCESS read-write
			STATUS current
			DESCRIPTION
				"It lights up when the module cannot insert in the backplane bus the audio channels Trap Enable"
		::= { adb2008c01v1Entry 60 }

		-- 1.3.6.1.4.1.10106.3.101291.1.1.61
		adb2008c01v1AudOvldFail OBJECT-TYPE
			SYNTAX BitFail
			MAX-ACCESS read-only
			STATUS current
			DESCRIPTION
				"Audio overload fail"
		::= { adb2008c01v1Entry 61 }

		-- 1.3.6.1.4.1.10106.3.101291.1.1.62
		adb2008c01v1AudOvldFailTrapEnable OBJECT-TYPE
			SYNTAX AlarmEnable
			MAX-ACCESS read-write
			STATUS current
			DESCRIPTION
				"Audio overload fail Trap Enable"
		::= { adb2008c01v1Entry 62 }

		-- 1.3.6.1.4.1.10106.3.101291.1.1.63
		adb2008c01v1Slot1Pres OBJECT-TYPE
			SYNTAX Bit0No1Yes
			MAX-ACCESS read-only
			STATUS current
			DESCRIPTION
				"Slot 1 data presence"
		::= { adb2008c01v1Entry 63 }

		-- 1.3.6.1.4.1.10106.3.101291.1.1.65
		adb2008c01v1Slot2Pres OBJECT-TYPE
			SYNTAX Bit0No1Yes
			MAX-ACCESS read-only
			STATUS current
			DESCRIPTION
				"Slot 2 data presence"
		::= { adb2008c01v1Entry 65 }

		-- 1.3.6.1.4.1.10106.3.101291.1.1.67
		adb2008c01v1Slot3Pres OBJECT-TYPE
			SYNTAX Bit0No1Yes
			MAX-ACCESS read-only
			STATUS current
			DESCRIPTION
				"Slot 3 data presence"
		::= { adb2008c01v1Entry 67 }

		-- 1.3.6.1.4.1.10106.3.101291.1.1.69
		adb2008c01v1Slot4Pres OBJECT-TYPE
			SYNTAX Bit0No1Yes
			MAX-ACCESS read-only
			STATUS current
			DESCRIPTION
				"Slot 4 data presence"
		::= { adb2008c01v1Entry 69 }

		-- 1.3.6.1.4.1.10106.3.101291.1.1.71
		adb2008c01v1Slot5Pres OBJECT-TYPE
			SYNTAX Bit0No1Yes
			MAX-ACCESS read-only
			STATUS current
			DESCRIPTION
				"Slot 5 data presence"
		::= { adb2008c01v1Entry 71 }

		-- 1.3.6.1.4.1.10106.3.101291.1.1.73
		adb2008c01v1Slot6Pres OBJECT-TYPE
			SYNTAX Bit0No1Yes
			MAX-ACCESS read-only
			STATUS current
			DESCRIPTION
				"Slot 6 data presence"
		::= { adb2008c01v1Entry 73 }

		-- 1.3.6.1.4.1.10106.3.101291.1.1.75
		adb2008c01v1Slot7Pres OBJECT-TYPE
			SYNTAX Bit0No1Yes
			MAX-ACCESS read-only
			STATUS current
			DESCRIPTION
				"Slot 7 data presence"
		::= { adb2008c01v1Entry 75 }

		-- 1.3.6.1.4.1.10106.3.101291.1.1.77
		adb2008c01v1Slot8Pres OBJECT-TYPE
			SYNTAX Bit0No1Yes
			MAX-ACCESS read-only
			STATUS current
			DESCRIPTION
				"Slot 8 data presence"
		::= { adb2008c01v1Entry 77 }

		-- 1.3.6.1.4.1.10106.3.101291.1.1.79
		adb2008c01v1SerialNo OBJECT-TYPE
			SYNTAX SerialNo
			MAX-ACCESS read-only
			STATUS current
			DESCRIPTION
				"Serial number"
		::= { adb2008c01v1Entry 79 }

		-- 1.3.6.1.4.1.10106.3.497601
		dab2008c01v1 OBJECT IDENTIFIER ::= { albalaProducts 497601 }

		-- 1.3.6.1.4.1.10106.3.497601.1
		dab2008c01v1Table  OBJECT-TYPE
			SYNTAX SEQUENCE OF Dab2008c01v1Entry
			MAX-ACCESS not-accessible
			STATUS current
			DESCRIPTION
				"Module  DAB2008C01V1 Table"
			::= { dab2008c01v1 1 }

		-- 1.3.6.1.4.1.10106.3.497601.1.1
		dab2008c01v1Entry  OBJECT-TYPE
			SYNTAX Dab2008c01v1Entry
			MAX-ACCESS not-accessible
			STATUS current
			DESCRIPTION
				"Module DAB2008C01V1 Entry"
			INDEX { dab2008c01v1Index }
			::= { dab2008c01v1Table 1 }

			Dab2008c01v1Entry ::=
			SEQUENCE {
				dab2008c01v1Index
				ModuleIndex,
				dab2008c01v1ActivePreset
				Preset16Active,
				dab2008c01v1LoadPreset
				Preset16Load,
				dab2008c01v1SavePreset
				Preset16Save,
				dab2008c01v1ManNAuto
				Bit0Aut1Man,
				dab2008c01v1BaseSlot
				Uint5,
				dab2008c01v1SlotUsed
				AdbDabSlot,
				dab2008c01v1OvldLevel
				LevelDbfsA,
				dab2008c01v1BusSyncFail
				BitFail,
				dab2008c01v1BusSyncFailTrapEnable
				AlarmEnable,
				dab2008c01v1BusSyncUnlck
				BitFail,
				dab2008c01v1BusSyncUnlckTrapEnable
				AlarmEnable,
				dab2008c01v1BusAudFail
				BitFail,
				dab2008c01v1BusAudFailTrapEnable
				AlarmEnable,
				dab2008c01v1BusAudError
				BitFail,
				dab2008c01v1BusAudErrorTrapEnable
				AlarmEnable,
				dab2008c01v1AudClipEr
				BitFail,
				dab2008c01v1AudClipErTrapEnable
				AlarmEnable,
				dab2008c01v1AudPresFail
				BitFail,
				dab2008c01v1AudPresFailTrapEnable
				AlarmEnable,
				dab2008c01v1AudOvldFail
				BitFail,
				dab2008c01v1AudOvldFailTrapEnable
				AlarmEnable,
				dab2008c01v1Slot1Pres
				Bit0No1Yes,
				dab2008c01v1Slot2Pres
				Bit0No1Yes,
				dab2008c01v1Slot3Pres
				Bit0No1Yes,
				dab2008c01v1Slot4Pres
				Bit0No1Yes,
				dab2008c01v1Slot5Pres
				Bit0No1Yes,
				dab2008c01v1Slot6Pres
				Bit0No1Yes,
				dab2008c01v1Slot7Pres
				Bit0No1Yes,
				dab2008c01v1Slot8Pres
				Bit0No1Yes,
				dab2008c01v1SerialNo
				SerialNo
			 }

		-- 1.3.6.1.4.1.10106.3.101291.1.1.1
		dab2008c01v1Index OBJECT-TYPE
			SYNTAX ModuleIndex
			MAX-ACCESS read-only
			STATUS current
			DESCRIPTION
				"Index of DAB2008C01V1 Table"
		::= { dab2008c01v1Entry 1 }

		-- 1.3.6.1.4.1.10106.3.101291.1.1.3
		dab2008c01v1ActivePreset OBJECT-TYPE
			SYNTAX Preset16Active
			MAX-ACCESS read-only
			STATUS current
			DESCRIPTION
				"Shows the active preset"
		::= { dab2008c01v1Entry 3 }

		-- 1.3.6.1.4.1.10106.3.101291.1.1.5
		dab2008c01v1LoadPreset OBJECT-TYPE
			SYNTAX Preset16Load
			MAX-ACCESS read-write
			STATUS current
			DESCRIPTION
				"Allows loading a preset"
		::= { dab2008c01v1Entry 5 }

		-- 1.3.6.1.4.1.10106.3.101291.1.1.7
		dab2008c01v1SavePreset OBJECT-TYPE
			SYNTAX Preset16Save
			MAX-ACCESS read-write
			STATUS current
			DESCRIPTION
				"Allows saving a preset"
		::= { dab2008c01v1Entry 7 }

		-- 1.3.6.1.4.1.10106.3.101291.1.1.9
		dab2008c01v1ManNAuto OBJECT-TYPE
			SYNTAX Bit0Aut1Man
			MAX-ACCESS read-write
			STATUS current
			DESCRIPTION
				"It allows selecting the slot working mode"
		::= { dab2008c01v1Entry 9 }

		-- 1.3.6.1.4.1.10106.3.101291.1.1.11
		dab2008c01v1BaseSlot OBJECT-TYPE
			SYNTAX Uint5
			MAX-ACCESS read-write
			STATUS current
			DESCRIPTION
				"Base rack slot"
		::= { dab2008c01v1Entry 11 }

		-- 1.3.6.1.4.1.10106.3.101291.1.1.13
		dab2008c01v1SlotUsed OBJECT-TYPE
			SYNTAX AdbDabSlot
			MAX-ACCESS read-write
			STATUS current
			DESCRIPTION
				"Employed slot (read)"
		::= { dab2008c01v1Entry 13 }

		-- 1.3.6.1.4.1.10106.3.101291.1.1.15
		dab2008c01v1OvldLevel OBJECT-TYPE
			SYNTAX LevelDbfsA
			MAX-ACCESS read-write
			STATUS current
			DESCRIPTION
				"It allows selecting the overload audio level"
		::= { dab2008c01v1Entry 15 }

		-- 1.3.6.1.4.1.10106.3.101291.1.1.17
		dab2008c01v1BusSyncFail OBJECT-TYPE
			SYNTAX BitFail
			MAX-ACCESS read-only
			STATUS current
			DESCRIPTION
				"Synchronization internal rack bus fail"
		::= { dab2008c01v1Entry 17 }

		-- 1.3.6.1.4.1.10106.3.101291.1.1.18
		dab2008c01v1BusSyncFailTrapEnable OBJECT-TYPE
			SYNTAX AlarmEnable
			MAX-ACCESS read-write
			STATUS current
			DESCRIPTION
				"Synchronization internal rack bus fail Trap Enable"
		::= { dab2008c01v1Entry 18 }

		-- 1.3.6.1.4.1.10106.3.101291.1.1.19
		dab2008c01v1BusSyncUnlck OBJECT-TYPE
			SYNTAX BitFail
			MAX-ACCESS read-only
			STATUS current
			DESCRIPTION
				"Synchronization internal rack bus unlocked"
		::= { dab2008c01v1Entry 19 }

		-- 1.3.6.1.4.1.10106.3.101291.1.1.20
		dab2008c01v1BusSyncUnlckTrapEnable OBJECT-TYPE
			SYNTAX AlarmEnable
			MAX-ACCESS read-write
			STATUS current
			DESCRIPTION
				"Synchronization internal rack bus unlocked Trap Enable"
		::= { dab2008c01v1Entry 20 }

		-- 1.3.6.1.4.1.10106.3.101291.1.1.21
		dab2008c01v1BusAudFail OBJECT-TYPE
			SYNTAX BitFail
			MAX-ACCESS read-only
			STATUS current
			DESCRIPTION
				"Audio bus fail"
		::= { dab2008c01v1Entry 21 }

		-- 1.3.6.1.4.1.10106.3.101291.1.1.22
		dab2008c01v1BusAudFailTrapEnable OBJECT-TYPE
			SYNTAX AlarmEnable
			MAX-ACCESS read-write
			STATUS current
			DESCRIPTION
				"Audio bus fail Trap Enable"
		::= { dab2008c01v1Entry 22 }

		-- 1.3.6.1.4.1.10106.3.101291.1.1.23
		dab2008c01v1BusAudError OBJECT-TYPE
			SYNTAX BitFail
			MAX-ACCESS read-only
			STATUS current
			DESCRIPTION
				"Audio bus errors"
		::= { dab2008c01v1Entry 23 }

		-- 1.3.6.1.4.1.10106.3.101291.1.1.24
		dab2008c01v1BusAudErrorTrapEnable OBJECT-TYPE
			SYNTAX AlarmEnable
			MAX-ACCESS read-write
			STATUS current
			DESCRIPTION
				"Audio bus errors Trap Enable"
		::= { dab2008c01v1Entry 24 }

		-- 1.3.6.1.4.1.10106.3.101291.1.1.25
		dab2008c01v1AudClipEr OBJECT-TYPE
			SYNTAX BitFail
			MAX-ACCESS read-only
			STATUS current
			DESCRIPTION
				"Audio clipping error"
		::= { dab2008c01v1Entry 25 }

		-- 1.3.6.1.4.1.10106.3.101291.1.1.26
		dab2008c01v1AudClipErTrapEnable OBJECT-TYPE
			SYNTAX AlarmEnable
			MAX-ACCESS read-write
			STATUS current
			DESCRIPTION
				"Audio clipping error Trap Enable"
		::= { dab2008c01v1Entry 26 }

		-- 1.3.6.1.4.1.10106.3.101291.1.1.27
		dab2008c01v1AudPresFail OBJECT-TYPE
			SYNTAX BitFail
			MAX-ACCESS read-only
			STATUS current
			DESCRIPTION
				"It lights up when the backplane bus does not have all the audio channels the module is required to read"
		::= { dab2008c01v1Entry 27 }

		-- 1.3.6.1.4.1.10106.3.101291.1.1.28
		dab2008c01v1AudPresFailTrapEnable OBJECT-TYPE
			SYNTAX AlarmEnable
			MAX-ACCESS read-write
			STATUS current
			DESCRIPTION
				"It lights up when the backplane bus does not have all the audio channels the module is required to read Trap Enable"
		::= { dab2008c01v1Entry 28 }

		-- 1.3.6.1.4.1.10106.3.101291.1.1.29
		dab2008c01v1AudOvldFail OBJECT-TYPE
			SYNTAX BitFail
			MAX-ACCESS read-only
			STATUS current
			DESCRIPTION
				"Audio overload fail"
		::= { dab2008c01v1Entry 29 }

		-- 1.3.6.1.4.1.10106.3.101291.1.1.30
		dab2008c01v1AudOvldFailTrapEnable OBJECT-TYPE
			SYNTAX AlarmEnable
			MAX-ACCESS read-write
			STATUS current
			DESCRIPTION
				"Audio overload fail Trap Enable"
		::= { dab2008c01v1Entry 30 }

		-- 1.3.6.1.4.1.10106.3.101291.1.1.31
		dab2008c01v1Slot1Pres OBJECT-TYPE
			SYNTAX Bit0No1Yes
			MAX-ACCESS read-only
			STATUS current
			DESCRIPTION
				"Slot 1 data presence"
		::= { dab2008c01v1Entry 31 }

		-- 1.3.6.1.4.1.10106.3.101291.1.1.33
		dab2008c01v1Slot2Pres OBJECT-TYPE
			SYNTAX Bit0No1Yes
			MAX-ACCESS read-only
			STATUS current
			DESCRIPTION
				"Slot 2 data presence"
		::= { dab2008c01v1Entry 33 }

		-- 1.3.6.1.4.1.10106.3.101291.1.1.35
		dab2008c01v1Slot3Pres OBJECT-TYPE
			SYNTAX Bit0No1Yes
			MAX-ACCESS read-only
			STATUS current
			DESCRIPTION
				"Slot 3 data presence"
		::= { dab2008c01v1Entry 35 }

		-- 1.3.6.1.4.1.10106.3.101291.1.1.37
		dab2008c01v1Slot4Pres OBJECT-TYPE
			SYNTAX Bit0No1Yes
			MAX-ACCESS read-only
			STATUS current
			DESCRIPTION
				"Slot 4 data presence"
		::= { dab2008c01v1Entry 37 }

		-- 1.3.6.1.4.1.10106.3.101291.1.1.39
		dab2008c01v1Slot5Pres OBJECT-TYPE
			SYNTAX Bit0No1Yes
			MAX-ACCESS read-only
			STATUS current
			DESCRIPTION
				"Slot 5 data presence"
		::= { dab2008c01v1Entry 39 }

		-- 1.3.6.1.4.1.10106.3.101291.1.1.41
		dab2008c01v1Slot6Pres OBJECT-TYPE
			SYNTAX Bit0No1Yes
			MAX-ACCESS read-only
			STATUS current
			DESCRIPTION
				"Slot 6 data presence"
		::= { dab2008c01v1Entry 41 }

		-- 1.3.6.1.4.1.10106.3.101291.1.1.43
		dab2008c01v1Slot7Pres OBJECT-TYPE
			SYNTAX Bit0No1Yes
			MAX-ACCESS read-only
			STATUS current
			DESCRIPTION
				"Slot 7 data presence"
		::= { dab2008c01v1Entry 43 }

		-- 1.3.6.1.4.1.10106.3.101291.1.1.45
		dab2008c01v1Slot8Pres OBJECT-TYPE
			SYNTAX Bit0No1Yes
			MAX-ACCESS read-only
			STATUS current
			DESCRIPTION
				"Slot 8 data presence"
		::= { dab2008c01v1Entry 45 }

		-- 1.3.6.1.4.1.10106.3.101291.1.1.47
		dab2008c01v1SerialNo OBJECT-TYPE
			SYNTAX SerialNo
			MAX-ACCESS read-only
			STATUS current
			DESCRIPTION
				"Serial number"
		::= { dab2008c01v1Entry 47 }

		-- 1.3.6.1.4.1.10106.3.497701
		ddb2008c01v1 OBJECT IDENTIFIER ::= { albalaProducts 497701 }

		-- 1.3.6.1.4.1.10106.3.497701.1
		ddb2008c01v1Table  OBJECT-TYPE
			SYNTAX SEQUENCE OF Ddb2008c01v1Entry
			MAX-ACCESS not-accessible
			STATUS current
			DESCRIPTION
				"Module  DDB2008C01V1 Table"
			::= { ddb2008c01v1 1 }

		-- 1.3.6.1.4.1.10106.3.497701.1.1
		ddb2008c01v1Entry  OBJECT-TYPE
			SYNTAX Ddb2008c01v1Entry
			MAX-ACCESS not-accessible
			STATUS current
			DESCRIPTION
				"Module DDB2008C01V1 Entry"
			INDEX { ddb2008c01v1Index }
			::= { ddb2008c01v1Table 1 }

			Ddb2008c01v1Entry ::=
			SEQUENCE {
				ddb2008c01v1Index
				ModuleIndex,
				ddb2008c01v1ActivePreset
				Preset16Active,
				ddb2008c01v1LoadPreset
				Preset16Load,
				ddb2008c01v1SavePreset
				Preset16Save,
				ddb2008c01v1ManNAuto
				Bit0Aut1Man,
				ddb2008c01v1AesInNOut
				Bit0Out1In,
				ddb2008c01v1BaseSlot
				Uint5,
				ddb2008c01v1SlotUsed
				DdbSlots,
				ddb2008c01v1OvldLevel
				LevelDbfsA,
				ddb2008c01v1Gain0
				Gain24dbMute,
				ddb2008c01v1Phase0
				Bit0Nor1Inv,
				ddb2008c01v1Gain1
				Gain24dbMute,
				ddb2008c01v1Phase1
				Bit0Nor1Inv,
				ddb2008c01v1Gain2
				Gain24dbMute,
				ddb2008c01v1Phase2
				Bit0Nor1Inv,
				ddb2008c01v1Gain3
				Gain24dbMute,
				ddb2008c01v1Phase3
				Bit0Nor1Inv,
				ddb2008c01v1Gain4
				Gain24dbMute,
				ddb2008c01v1Phase4
				Bit0Nor1Inv,
				ddb2008c01v1Gain5
				Gain24dbMute,
				ddb2008c01v1Phase5
				Bit0Nor1Inv,
				ddb2008c01v1Gain6
				Gain24dbMute,
				ddb2008c01v1Phase6
				Bit0Nor1Inv,
				ddb2008c01v1Gain7
				Gain24dbMute,
				ddb2008c01v1Phase7
				Bit0Nor1Inv,
				ddb2008c01v1Gain8
				Gain24dbMute,
				ddb2008c01v1Phase8
				Bit0Nor1Inv,
				ddb2008c01v1Gain9
				Gain24dbMute,
				ddb2008c01v1Phase9
				Bit0Nor1Inv,
				ddb2008c01v1Gain10
				Gain24dbMute,
				ddb2008c01v1Phase10
				Bit0Nor1Inv,
				ddb2008c01v1Gain11
				Gain24dbMute,
				ddb2008c01v1Phase11
				Bit0Nor1Inv,
				ddb2008c01v1Gain12
				Gain24dbMute,
				ddb2008c01v1Phase12
				Bit0Nor1Inv,
				ddb2008c01v1Gain13
				Gain24dbMute,
				ddb2008c01v1Phase13
				Bit0Nor1Inv,
				ddb2008c01v1Gain14
				Gain24dbMute,
				ddb2008c01v1Phase14
				Bit0Nor1Inv,
				ddb2008c01v1Gain15
				Gain24dbMute,
				ddb2008c01v1Phase15
				Bit0Nor1Inv,
				ddb2008c01v1BusTimFail
				BitFail,
				ddb2008c01v1BusTimFailTrapEnable
				AlarmEnable,
				ddb2008c01v1BusTimUnlck
				BitFail,
				ddb2008c01v1BusTimUnlckTrapEnable
				AlarmEnable,
				ddb2008c01v1BusAudFail
				BitFail,
				ddb2008c01v1BusAudFailTrapEnable
				AlarmEnable,
				ddb2008c01v1BusAudError
				BitFail,
				ddb2008c01v1BusAudErrorTrapEnable
				AlarmEnable,
				ddb2008c01v1AudClipEr
				BitFail,
				ddb2008c01v1AudClipErTrapEnable
				AlarmEnable,
				ddb2008c01v1AudPresFail
				BitFail,
				ddb2008c01v1AudPresFailTrapEnable
				AlarmEnable,
				ddb2008c01v1AudInsFail
				BitFail,
				ddb2008c01v1AudInsFailTrapEnable
				AlarmEnable,
				ddb2008c01v1AudOvldEr
				BitFail,
				ddb2008c01v1AudOvldErTrapEnable
				AlarmEnable,
				ddb2008c01v1Slot1Pres
				Bit0No1Yes,
				ddb2008c01v1Slot2Pres
				Bit0No1Yes,
				ddb2008c01v1Slot3Pres
				Bit0No1Yes,
				ddb2008c01v1Slot4Pres
				Bit0No1Yes,
				ddb2008c01v1Slot5Pres
				Bit0No1Yes,
				ddb2008c01v1Slot6Pres
				Bit0No1Yes,
				ddb2008c01v1Slot7Pres
				Bit0No1Yes,
				ddb2008c01v1Slot8Pres
				Bit0No1Yes,
				ddb2008c01v1Aes1Pres
				Bit0No1Yes,
				ddb2008c01v1Aes2Pres
				Bit0No1Yes,
				ddb2008c01v1Aes3Pres
				Bit0No1Yes,
				ddb2008c01v1Aes4Pres
				Bit0No1Yes,
				ddb2008c01v1Aes5Pres
				Bit0No1Yes,
				ddb2008c01v1Aes6Pres
				Bit0No1Yes,
				ddb2008c01v1Aes7Pres
				Bit0No1Yes,
				ddb2008c01v1Aes8Pres
				Bit0No1Yes,
				ddb2008c01v1Aes1AsyncFail
				BitFail,
				ddb2008c01v1Aes2AsyncFail
				BitFail,
				ddb2008c01v1Aes3AsyncFail
				BitFail,
				ddb2008c01v1Aes4AsyncFail
				BitFail,
				ddb2008c01v1Aes5AsyncFail
				BitFail,
				ddb2008c01v1Aes6AsyncFail
				BitFail,
				ddb2008c01v1Aes7AsyncFail
				BitFail,
				ddb2008c01v1Aes8AsyncFail
				BitFail,
				ddb2008c01v1SerialNo
				SerialNo
			 }

		-- 1.3.6.1.4.1.10106.3.101291.1.1.1
		ddb2008c01v1Index OBJECT-TYPE
			SYNTAX ModuleIndex
			MAX-ACCESS read-only
			STATUS current
			DESCRIPTION
				"Index of DDB2008C01V1 Table"
		::= { ddb2008c01v1Entry 1 }

		-- 1.3.6.1.4.1.10106.3.101291.1.1.3
		ddb2008c01v1ActivePreset OBJECT-TYPE
			SYNTAX Preset16Active
			MAX-ACCESS read-only
			STATUS current
			DESCRIPTION
				"Shows the active preset"
		::= { ddb2008c01v1Entry 3 }

		-- 1.3.6.1.4.1.10106.3.101291.1.1.5
		ddb2008c01v1LoadPreset OBJECT-TYPE
			SYNTAX Preset16Load
			MAX-ACCESS read-write
			STATUS current
			DESCRIPTION
				"Allows loading a preset"
		::= { ddb2008c01v1Entry 5 }

		-- 1.3.6.1.4.1.10106.3.101291.1.1.7
		ddb2008c01v1SavePreset OBJECT-TYPE
			SYNTAX Preset16Save
			MAX-ACCESS read-write
			STATUS current
			DESCRIPTION
				"Allows saving a preset"
		::= { ddb2008c01v1Entry 7 }

		-- 1.3.6.1.4.1.10106.3.101291.1.1.9
		ddb2008c01v1ManNAuto OBJECT-TYPE
			SYNTAX Bit0Aut1Man
			MAX-ACCESS read-write
			STATUS current
			DESCRIPTION
				"It allows selecting the slot working mode"
		::= { ddb2008c01v1Entry 9 }

		-- 1.3.6.1.4.1.10106.3.101291.1.1.11
		ddb2008c01v1AesInNOut OBJECT-TYPE
			SYNTAX Bit0Out1In
			MAX-ACCESS read-write
			STATUS current
			DESCRIPTION
				"It allows selecting whether the AES signals are inputs or outputs"
		::= { ddb2008c01v1Entry 11 }

		-- 1.3.6.1.4.1.10106.3.101291.1.1.13
		ddb2008c01v1BaseSlot OBJECT-TYPE
			SYNTAX Uint5
			MAX-ACCESS read-write
			STATUS current
			DESCRIPTION
				"Base rack slot"
		::= { ddb2008c01v1Entry 13 }

		-- 1.3.6.1.4.1.10106.3.101291.1.1.15
		ddb2008c01v1SlotUsed OBJECT-TYPE
			SYNTAX DdbSlots
			MAX-ACCESS read-write
			STATUS current
			DESCRIPTION
				"Employed slots"
		::= { ddb2008c01v1Entry 15 }

		-- 1.3.6.1.4.1.10106.3.101291.1.1.17
		ddb2008c01v1OvldLevel OBJECT-TYPE
			SYNTAX LevelDbfsA
			MAX-ACCESS read-write
			STATUS current
			DESCRIPTION
				"It allows selecting the overload audio level"
		::= { ddb2008c01v1Entry 17 }

		-- 1.3.6.1.4.1.10106.3.101291.1.1.19
		ddb2008c01v1Gain0 OBJECT-TYPE
			SYNTAX Gain24dbMute
			MAX-ACCESS read-write
			STATUS current
			DESCRIPTION
				"Gain applied to the left channel of AES1"
		::= { ddb2008c01v1Entry 19 }

		-- 1.3.6.1.4.1.10106.3.101291.1.1.21
		ddb2008c01v1Phase0 OBJECT-TYPE
			SYNTAX Bit0Nor1Inv
			MAX-ACCESS read-write
			STATUS current
			DESCRIPTION
				"Phase gain applied to the left channel of AES1"
		::= { ddb2008c01v1Entry 21 }

		-- 1.3.6.1.4.1.10106.3.101291.1.1.23
		ddb2008c01v1Gain1 OBJECT-TYPE
			SYNTAX Gain24dbMute
			MAX-ACCESS read-write
			STATUS current
			DESCRIPTION
				"Gain applied to the right channel of AES1"
		::= { ddb2008c01v1Entry 23 }

		-- 1.3.6.1.4.1.10106.3.101291.1.1.25
		ddb2008c01v1Phase1 OBJECT-TYPE
			SYNTAX Bit0Nor1Inv
			MAX-ACCESS read-write
			STATUS current
			DESCRIPTION
				"Phase gain applied to the right channel of AES1"
		::= { ddb2008c01v1Entry 25 }

		-- 1.3.6.1.4.1.10106.3.101291.1.1.27
		ddb2008c01v1Gain2 OBJECT-TYPE
			SYNTAX Gain24dbMute
			MAX-ACCESS read-write
			STATUS current
			DESCRIPTION
				"Gain applied to the left channel of AES2"
		::= { ddb2008c01v1Entry 27 }

		-- 1.3.6.1.4.1.10106.3.101291.1.1.29
		ddb2008c01v1Phase2 OBJECT-TYPE
			SYNTAX Bit0Nor1Inv
			MAX-ACCESS read-write
			STATUS current
			DESCRIPTION
				"Phase gain applied to the left channel of AES2"
		::= { ddb2008c01v1Entry 29 }

		-- 1.3.6.1.4.1.10106.3.101291.1.1.31
		ddb2008c01v1Gain3 OBJECT-TYPE
			SYNTAX Gain24dbMute
			MAX-ACCESS read-write
			STATUS current
			DESCRIPTION
				"Gain applied to the right channel of AES2"
		::= { ddb2008c01v1Entry 31 }

		-- 1.3.6.1.4.1.10106.3.101291.1.1.33
		ddb2008c01v1Phase3 OBJECT-TYPE
			SYNTAX Bit0Nor1Inv
			MAX-ACCESS read-write
			STATUS current
			DESCRIPTION
				"Phase gain applied to the right channel of AES2"
		::= { ddb2008c01v1Entry 33 }

		-- 1.3.6.1.4.1.10106.3.101291.1.1.35
		ddb2008c01v1Gain4 OBJECT-TYPE
			SYNTAX Gain24dbMute
			MAX-ACCESS read-write
			STATUS current
			DESCRIPTION
				"Gain applied to the left channel of AES3"
		::= { ddb2008c01v1Entry 35 }

		-- 1.3.6.1.4.1.10106.3.101291.1.1.37
		ddb2008c01v1Phase4 OBJECT-TYPE
			SYNTAX Bit0Nor1Inv
			MAX-ACCESS read-write
			STATUS current
			DESCRIPTION
				"Phase gain applied to the left channel of AES3"
		::= { ddb2008c01v1Entry 37 }

		-- 1.3.6.1.4.1.10106.3.101291.1.1.39
		ddb2008c01v1Gain5 OBJECT-TYPE
			SYNTAX Gain24dbMute
			MAX-ACCESS read-write
			STATUS current
			DESCRIPTION
				"Gain applied to the right channel of AES3"
		::= { ddb2008c01v1Entry 39 }

		-- 1.3.6.1.4.1.10106.3.101291.1.1.41
		ddb2008c01v1Phase5 OBJECT-TYPE
			SYNTAX Bit0Nor1Inv
			MAX-ACCESS read-write
			STATUS current
			DESCRIPTION
				"Phase gain applied to the right channel of AES3"
		::= { ddb2008c01v1Entry 41 }

		-- 1.3.6.1.4.1.10106.3.101291.1.1.43
		ddb2008c01v1Gain6 OBJECT-TYPE
			SYNTAX Gain24dbMute
			MAX-ACCESS read-write
			STATUS current
			DESCRIPTION
				"Gain applied to the left channel of AES4"
		::= { ddb2008c01v1Entry 43 }

		-- 1.3.6.1.4.1.10106.3.101291.1.1.45
		ddb2008c01v1Phase6 OBJECT-TYPE
			SYNTAX Bit0Nor1Inv
			MAX-ACCESS read-write
			STATUS current
			DESCRIPTION
				"Phase gain applied to the left channel of AES4"
		::= { ddb2008c01v1Entry 45 }

		-- 1.3.6.1.4.1.10106.3.101291.1.1.47
		ddb2008c01v1Gain7 OBJECT-TYPE
			SYNTAX Gain24dbMute
			MAX-ACCESS read-write
			STATUS current
			DESCRIPTION
				"Gain applied to the right channel of AES4"
		::= { ddb2008c01v1Entry 47 }

		-- 1.3.6.1.4.1.10106.3.101291.1.1.49
		ddb2008c01v1Phase7 OBJECT-TYPE
			SYNTAX Bit0Nor1Inv
			MAX-ACCESS read-write
			STATUS current
			DESCRIPTION
				"Phase gain applied to the right channel of AES4"
		::= { ddb2008c01v1Entry 49 }

		-- 1.3.6.1.4.1.10106.3.101291.1.1.51
		ddb2008c01v1Gain8 OBJECT-TYPE
			SYNTAX Gain24dbMute
			MAX-ACCESS read-write
			STATUS current
			DESCRIPTION
				"Gain applied to the left channel of AES5"
		::= { ddb2008c01v1Entry 51 }

		-- 1.3.6.1.4.1.10106.3.101291.1.1.53
		ddb2008c01v1Phase8 OBJECT-TYPE
			SYNTAX Bit0Nor1Inv
			MAX-ACCESS read-write
			STATUS current
			DESCRIPTION
				"Phase gain applied to the left channel of AES5"
		::= { ddb2008c01v1Entry 53 }

		-- 1.3.6.1.4.1.10106.3.101291.1.1.55
		ddb2008c01v1Gain9 OBJECT-TYPE
			SYNTAX Gain24dbMute
			MAX-ACCESS read-write
			STATUS current
			DESCRIPTION
				"Gain applied to the right channel of AES5"
		::= { ddb2008c01v1Entry 55 }

		-- 1.3.6.1.4.1.10106.3.101291.1.1.57
		ddb2008c01v1Phase9 OBJECT-TYPE
			SYNTAX Bit0Nor1Inv
			MAX-ACCESS read-write
			STATUS current
			DESCRIPTION
				"Phase gain applied to the right channel of AES5"
		::= { ddb2008c01v1Entry 57 }

		-- 1.3.6.1.4.1.10106.3.101291.1.1.59
		ddb2008c01v1Gain10 OBJECT-TYPE
			SYNTAX Gain24dbMute
			MAX-ACCESS read-write
			STATUS current
			DESCRIPTION
				"Gain applied to the left channel of AES6"
		::= { ddb2008c01v1Entry 59 }

		-- 1.3.6.1.4.1.10106.3.101291.1.1.61
		ddb2008c01v1Phase10 OBJECT-TYPE
			SYNTAX Bit0Nor1Inv
			MAX-ACCESS read-write
			STATUS current
			DESCRIPTION
				"Phase gain applied to the left channel of AES6"
		::= { ddb2008c01v1Entry 61 }

		-- 1.3.6.1.4.1.10106.3.101291.1.1.63
		ddb2008c01v1Gain11 OBJECT-TYPE
			SYNTAX Gain24dbMute
			MAX-ACCESS read-write
			STATUS current
			DESCRIPTION
				"Gain applied to the right channel of AES6"
		::= { ddb2008c01v1Entry 63 }

		-- 1.3.6.1.4.1.10106.3.101291.1.1.65
		ddb2008c01v1Phase11 OBJECT-TYPE
			SYNTAX Bit0Nor1Inv
			MAX-ACCESS read-write
			STATUS current
			DESCRIPTION
				"Phase gain applied to the right channel of AES6"
		::= { ddb2008c01v1Entry 65 }

		-- 1.3.6.1.4.1.10106.3.101291.1.1.67
		ddb2008c01v1Gain12 OBJECT-TYPE
			SYNTAX Gain24dbMute
			MAX-ACCESS read-write
			STATUS current
			DESCRIPTION
				"Gain applied to the left channel of AES7"
		::= { ddb2008c01v1Entry 67 }

		-- 1.3.6.1.4.1.10106.3.101291.1.1.69
		ddb2008c01v1Phase12 OBJECT-TYPE
			SYNTAX Bit0Nor1Inv
			MAX-ACCESS read-write
			STATUS current
			DESCRIPTION
				"Phase gain applied to the left channel of AES7"
		::= { ddb2008c01v1Entry 69 }

		-- 1.3.6.1.4.1.10106.3.101291.1.1.71
		ddb2008c01v1Gain13 OBJECT-TYPE
			SYNTAX Gain24dbMute
			MAX-ACCESS read-write
			STATUS current
			DESCRIPTION
				"Gain applied to the right channel of AES7"
		::= { ddb2008c01v1Entry 71 }

		-- 1.3.6.1.4.1.10106.3.101291.1.1.73
		ddb2008c01v1Phase13 OBJECT-TYPE
			SYNTAX Bit0Nor1Inv
			MAX-ACCESS read-write
			STATUS current
			DESCRIPTION
				"Phase gain applied to the right channel of AES7"
		::= { ddb2008c01v1Entry 73 }

		-- 1.3.6.1.4.1.10106.3.101291.1.1.75
		ddb2008c01v1Gain14 OBJECT-TYPE
			SYNTAX Gain24dbMute
			MAX-ACCESS read-write
			STATUS current
			DESCRIPTION
				"Gain applied to the left channel of AES8"
		::= { ddb2008c01v1Entry 75 }

		-- 1.3.6.1.4.1.10106.3.101291.1.1.77
		ddb2008c01v1Phase14 OBJECT-TYPE
			SYNTAX Bit0Nor1Inv
			MAX-ACCESS read-write
			STATUS current
			DESCRIPTION
				"Phase gain applied to the left channel of AES8"
		::= { ddb2008c01v1Entry 77 }

		-- 1.3.6.1.4.1.10106.3.101291.1.1.79
		ddb2008c01v1Gain15 OBJECT-TYPE
			SYNTAX Gain24dbMute
			MAX-ACCESS read-write
			STATUS current
			DESCRIPTION
				"Gain applied to the right channel of AES8"
		::= { ddb2008c01v1Entry 79 }

		-- 1.3.6.1.4.1.10106.3.101291.1.1.81
		ddb2008c01v1Phase15 OBJECT-TYPE
			SYNTAX Bit0Nor1Inv
			MAX-ACCESS read-write
			STATUS current
			DESCRIPTION
				"Phase gain applied to the right channel of AES8"
		::= { ddb2008c01v1Entry 81 }

		-- 1.3.6.1.4.1.10106.3.101291.1.1.83
		ddb2008c01v1BusTimFail OBJECT-TYPE
			SYNTAX BitFail
			MAX-ACCESS read-only
			STATUS current
			DESCRIPTION
				"Synchronization internal rack bus fail"
		::= { ddb2008c01v1Entry 83 }

		-- 1.3.6.1.4.1.10106.3.101291.1.1.84
		ddb2008c01v1BusTimFailTrapEnable OBJECT-TYPE
			SYNTAX AlarmEnable
			MAX-ACCESS read-write
			STATUS current
			DESCRIPTION
				"Synchronization internal rack bus fail Trap Enable"
		::= { ddb2008c01v1Entry 84 }

		-- 1.3.6.1.4.1.10106.3.101291.1.1.85
		ddb2008c01v1BusTimUnlck OBJECT-TYPE
			SYNTAX BitFail
			MAX-ACCESS read-only
			STATUS current
			DESCRIPTION
				"Synchronization internal rack bus unlocked"
		::= { ddb2008c01v1Entry 85 }

		-- 1.3.6.1.4.1.10106.3.101291.1.1.86
		ddb2008c01v1BusTimUnlckTrapEnable OBJECT-TYPE
			SYNTAX AlarmEnable
			MAX-ACCESS read-write
			STATUS current
			DESCRIPTION
				"Synchronization internal rack bus unlocked Trap Enable"
		::= { ddb2008c01v1Entry 86 }

		-- 1.3.6.1.4.1.10106.3.101291.1.1.87
		ddb2008c01v1BusAudFail OBJECT-TYPE
			SYNTAX BitFail
			MAX-ACCESS read-only
			STATUS current
			DESCRIPTION
				"Audio bus fail"
		::= { ddb2008c01v1Entry 87 }

		-- 1.3.6.1.4.1.10106.3.101291.1.1.88
		ddb2008c01v1BusAudFailTrapEnable OBJECT-TYPE
			SYNTAX AlarmEnable
			MAX-ACCESS read-write
			STATUS current
			DESCRIPTION
				"Audio bus fail Trap Enable"
		::= { ddb2008c01v1Entry 88 }

		-- 1.3.6.1.4.1.10106.3.101291.1.1.89
		ddb2008c01v1BusAudError OBJECT-TYPE
			SYNTAX BitFail
			MAX-ACCESS read-only
			STATUS current
			DESCRIPTION
				"Audio bus errors"
		::= { ddb2008c01v1Entry 89 }

		-- 1.3.6.1.4.1.10106.3.101291.1.1.90
		ddb2008c01v1BusAudErrorTrapEnable OBJECT-TYPE
			SYNTAX AlarmEnable
			MAX-ACCESS read-write
			STATUS current
			DESCRIPTION
				"Audio bus errors Trap Enable"
		::= { ddb2008c01v1Entry 90 }

		-- 1.3.6.1.4.1.10106.3.101291.1.1.91
		ddb2008c01v1AudClipEr OBJECT-TYPE
			SYNTAX BitFail
			MAX-ACCESS read-only
			STATUS current
			DESCRIPTION
				"Audio clipping error"
		::= { ddb2008c01v1Entry 91 }

		-- 1.3.6.1.4.1.10106.3.101291.1.1.92
		ddb2008c01v1AudClipErTrapEnable OBJECT-TYPE
			SYNTAX AlarmEnable
			MAX-ACCESS read-write
			STATUS current
			DESCRIPTION
				"Audio clipping error Trap Enable"
		::= { ddb2008c01v1Entry 92 }

		-- 1.3.6.1.4.1.10106.3.101291.1.1.93
		ddb2008c01v1AudPresFail OBJECT-TYPE
			SYNTAX BitFail
			MAX-ACCESS read-only
			STATUS current
			DESCRIPTION
				"It lights up when the backplane bus does not have all the audio channels the module is required to read"
		::= { ddb2008c01v1Entry 93 }

		-- 1.3.6.1.4.1.10106.3.101291.1.1.94
		ddb2008c01v1AudPresFailTrapEnable OBJECT-TYPE
			SYNTAX AlarmEnable
			MAX-ACCESS read-write
			STATUS current
			DESCRIPTION
				"It lights up when the backplane bus does not have all the audio channels the module is required to read Trap Enable"
		::= { ddb2008c01v1Entry 94 }

		-- 1.3.6.1.4.1.10106.3.101291.1.1.95
		ddb2008c01v1AudInsFail OBJECT-TYPE
			SYNTAX BitFail
			MAX-ACCESS read-only
			STATUS current
			DESCRIPTION
				"It lights up when the module cannot insert in the backplane bus the audio channels"
		::= { ddb2008c01v1Entry 95 }

		-- 1.3.6.1.4.1.10106.3.101291.1.1.96
		ddb2008c01v1AudInsFailTrapEnable OBJECT-TYPE
			SYNTAX AlarmEnable
			MAX-ACCESS read-write
			STATUS current
			DESCRIPTION
				"It lights up when the module cannot insert in the backplane bus the audio channels Trap Enable"
		::= { ddb2008c01v1Entry 96 }

		-- 1.3.6.1.4.1.10106.3.101291.1.1.97
		ddb2008c01v1AudOvldEr OBJECT-TYPE
			SYNTAX BitFail
			MAX-ACCESS read-only
			STATUS current
			DESCRIPTION
				"Audio overload fail"
		::= { ddb2008c01v1Entry 97 }

		-- 1.3.6.1.4.1.10106.3.101291.1.1.98
		ddb2008c01v1AudOvldErTrapEnable OBJECT-TYPE
			SYNTAX AlarmEnable
			MAX-ACCESS read-write
			STATUS current
			DESCRIPTION
				"Audio overload fail Trap Enable"
		::= { ddb2008c01v1Entry 98 }

		-- 1.3.6.1.4.1.10106.3.101291.1.1.99
		ddb2008c01v1Slot1Pres OBJECT-TYPE
			SYNTAX Bit0No1Yes
			MAX-ACCESS read-only
			STATUS current
			DESCRIPTION
				"Slot 1 data presence"
		::= { ddb2008c01v1Entry 99 }

		-- 1.3.6.1.4.1.10106.3.101291.1.1.101
		ddb2008c01v1Slot2Pres OBJECT-TYPE
			SYNTAX Bit0No1Yes
			MAX-ACCESS read-only
			STATUS current
			DESCRIPTION
				"Slot 2 data presence"
		::= { ddb2008c01v1Entry 101 }

		-- 1.3.6.1.4.1.10106.3.101291.1.1.103
		ddb2008c01v1Slot3Pres OBJECT-TYPE
			SYNTAX Bit0No1Yes
			MAX-ACCESS read-only
			STATUS current
			DESCRIPTION
				"Slot 3 data presence"
		::= { ddb2008c01v1Entry 103 }

		-- 1.3.6.1.4.1.10106.3.101291.1.1.105
		ddb2008c01v1Slot4Pres OBJECT-TYPE
			SYNTAX Bit0No1Yes
			MAX-ACCESS read-only
			STATUS current
			DESCRIPTION
				"Slot 4 data presence"
		::= { ddb2008c01v1Entry 105 }

		-- 1.3.6.1.4.1.10106.3.101291.1.1.107
		ddb2008c01v1Slot5Pres OBJECT-TYPE
			SYNTAX Bit0No1Yes
			MAX-ACCESS read-only
			STATUS current
			DESCRIPTION
				"Slot 5 data presence"
		::= { ddb2008c01v1Entry 107 }

		-- 1.3.6.1.4.1.10106.3.101291.1.1.109
		ddb2008c01v1Slot6Pres OBJECT-TYPE
			SYNTAX Bit0No1Yes
			MAX-ACCESS read-only
			STATUS current
			DESCRIPTION
				"Slot 6 data presence"
		::= { ddb2008c01v1Entry 109 }

		-- 1.3.6.1.4.1.10106.3.101291.1.1.111
		ddb2008c01v1Slot7Pres OBJECT-TYPE
			SYNTAX Bit0No1Yes
			MAX-ACCESS read-only
			STATUS current
			DESCRIPTION
				"Slot 7 data presence"
		::= { ddb2008c01v1Entry 111 }

		-- 1.3.6.1.4.1.10106.3.101291.1.1.113
		ddb2008c01v1Slot8Pres OBJECT-TYPE
			SYNTAX Bit0No1Yes
			MAX-ACCESS read-only
			STATUS current
			DESCRIPTION
				"Slot 8 data presence"
		::= { ddb2008c01v1Entry 113 }

		-- 1.3.6.1.4.1.10106.3.101291.1.1.115
		ddb2008c01v1Aes1Pres OBJECT-TYPE
			SYNTAX Bit0No1Yes
			MAX-ACCESS read-only
			STATUS current
			DESCRIPTION
				"AES1 presence"
		::= { ddb2008c01v1Entry 115 }

		-- 1.3.6.1.4.1.10106.3.101291.1.1.117
		ddb2008c01v1Aes2Pres OBJECT-TYPE
			SYNTAX Bit0No1Yes
			MAX-ACCESS read-only
			STATUS current
			DESCRIPTION
				"AES2 presence"
		::= { ddb2008c01v1Entry 117 }

		-- 1.3.6.1.4.1.10106.3.101291.1.1.119
		ddb2008c01v1Aes3Pres OBJECT-TYPE
			SYNTAX Bit0No1Yes
			MAX-ACCESS read-only
			STATUS current
			DESCRIPTION
				"AES3 presence"
		::= { ddb2008c01v1Entry 119 }

		-- 1.3.6.1.4.1.10106.3.101291.1.1.121
		ddb2008c01v1Aes4Pres OBJECT-TYPE
			SYNTAX Bit0No1Yes
			MAX-ACCESS read-only
			STATUS current
			DESCRIPTION
				"AES4 presence"
		::= { ddb2008c01v1Entry 121 }

		-- 1.3.6.1.4.1.10106.3.101291.1.1.123
		ddb2008c01v1Aes5Pres OBJECT-TYPE
			SYNTAX Bit0No1Yes
			MAX-ACCESS read-only
			STATUS current
			DESCRIPTION
				"AES5 presence"
		::= { ddb2008c01v1Entry 123 }

		-- 1.3.6.1.4.1.10106.3.101291.1.1.125
		ddb2008c01v1Aes6Pres OBJECT-TYPE
			SYNTAX Bit0No1Yes
			MAX-ACCESS read-only
			STATUS current
			DESCRIPTION
				"AES6 presence"
		::= { ddb2008c01v1Entry 125 }

		-- 1.3.6.1.4.1.10106.3.101291.1.1.127
		ddb2008c01v1Aes7Pres OBJECT-TYPE
			SYNTAX Bit0No1Yes
			MAX-ACCESS read-only
			STATUS current
			DESCRIPTION
				"AES7 presence"
		::= { ddb2008c01v1Entry 127 }

		-- 1.3.6.1.4.1.10106.3.101291.1.1.129
		ddb2008c01v1Aes8Pres OBJECT-TYPE
			SYNTAX Bit0No1Yes
			MAX-ACCESS read-only
			STATUS current
			DESCRIPTION
				"AES8 presence"
		::= { ddb2008c01v1Entry 129 }

		-- 1.3.6.1.4.1.10106.3.101291.1.1.131
		ddb2008c01v1Aes1AsyncFail OBJECT-TYPE
			SYNTAX BitFail
			MAX-ACCESS read-only
			STATUS current
			DESCRIPTION
				"AES1 asynchronous fail"
		::= { ddb2008c01v1Entry 131 }

		-- 1.3.6.1.4.1.10106.3.101291.1.1.133
		ddb2008c01v1Aes2AsyncFail OBJECT-TYPE
			SYNTAX BitFail
			MAX-ACCESS read-only
			STATUS current
			DESCRIPTION
				"AES2 asynchronous fail"
		::= { ddb2008c01v1Entry 133 }

		-- 1.3.6.1.4.1.10106.3.101291.1.1.135
		ddb2008c01v1Aes3AsyncFail OBJECT-TYPE
			SYNTAX BitFail
			MAX-ACCESS read-only
			STATUS current
			DESCRIPTION
				"AES3 asynchronous fail"
		::= { ddb2008c01v1Entry 135 }

		-- 1.3.6.1.4.1.10106.3.101291.1.1.137
		ddb2008c01v1Aes4AsyncFail OBJECT-TYPE
			SYNTAX BitFail
			MAX-ACCESS read-only
			STATUS current
			DESCRIPTION
				"AES4 asynchronous fail"
		::= { ddb2008c01v1Entry 137 }

		-- 1.3.6.1.4.1.10106.3.101291.1.1.139
		ddb2008c01v1Aes5AsyncFail OBJECT-TYPE
			SYNTAX BitFail
			MAX-ACCESS read-only
			STATUS current
			DESCRIPTION
				"AES5 asynchronous fail"
		::= { ddb2008c01v1Entry 139 }

		-- 1.3.6.1.4.1.10106.3.101291.1.1.141
		ddb2008c01v1Aes6AsyncFail OBJECT-TYPE
			SYNTAX BitFail
			MAX-ACCESS read-only
			STATUS current
			DESCRIPTION
				"AES6 asynchronous fail"
		::= { ddb2008c01v1Entry 141 }

		-- 1.3.6.1.4.1.10106.3.101291.1.1.143
		ddb2008c01v1Aes7AsyncFail OBJECT-TYPE
			SYNTAX BitFail
			MAX-ACCESS read-only
			STATUS current
			DESCRIPTION
				"AES7 asynchronous fail"
		::= { ddb2008c01v1Entry 143 }

		-- 1.3.6.1.4.1.10106.3.101291.1.1.145
		ddb2008c01v1Aes8AsyncFail OBJECT-TYPE
			SYNTAX BitFail
			MAX-ACCESS read-only
			STATUS current
			DESCRIPTION
				"AES8 asynchronous fail"
		::= { ddb2008c01v1Entry 145 }

		-- 1.3.6.1.4.1.10106.3.101291.1.1.147
		ddb2008c01v1SerialNo OBJECT-TYPE
			SYNTAX SerialNo
			MAX-ACCESS read-only
			STATUS current
			DESCRIPTION
				"Serial number"
		::= { ddb2008c01v1Entry 147 }

		-- 1.3.6.1.4.1.10106.3.514901
		smc2000c01v1 OBJECT IDENTIFIER ::= { albalaProducts 514901 }

		-- 1.3.6.1.4.1.10106.3.514901.1
		smc2000c01v1Table  OBJECT-TYPE
			SYNTAX SEQUENCE OF Smc2000c01v1Entry
			MAX-ACCESS not-accessible
			STATUS current
			DESCRIPTION
				"Module  SMC2000C01V1 Table"
			::= { smc2000c01v1 1 }

		-- 1.3.6.1.4.1.10106.3.514901.1.1
		smc2000c01v1Entry  OBJECT-TYPE
			SYNTAX Smc2000c01v1Entry
			MAX-ACCESS not-accessible
			STATUS current
			DESCRIPTION
				"Module SMC2000C01V1 Entry"
			INDEX { smc2000c01v1Index }
			::= { smc2000c01v1Table 1 }

			Smc2000c01v1Entry ::=
			SEQUENCE {
				smc2000c01v1Index
				ModuleIndex,
				smc2000c01v1P1EthMode
				EthMode2000,
				smc2000c01v1P2EthMode
				EthMode2000,
				smc2000c01v1PoEthMode
				EthMode2g5,
				smc2000c01v1SfpPres
				BitFailN,
				smc2000c01v1SfpPresTrapEnable
				AlarmEnable,
				smc2000c01v1SfpFail
				BitFail,
				smc2000c01v1SfpFailTrapEnable
				AlarmEnable,
				smc2000c01v1SfpLos
				BitFail,
				smc2000c01v1SfpLosTrapEnable
				AlarmEnable,
				smc2000c01v1SfpDiagSupport
				BitFailN,
				smc2000c01v1P1Status
				Smc2EthModeSt,
				smc2000c01v1P1StatusTrapEnable
				AlarmEnable,
				smc2000c01v1P2Status
				Smc2EthModeSt,
				smc2000c01v1P2StatusTrapEnable
				AlarmEnable,
				smc2000c01v1PoStatus
				Smc2EthModeSt,
				smc2000c01v1PoStatusTrapEnable
				AlarmEnable,
				smc2000c01v1SfpPower
				OptPowerX2Uw,
				smc2000c01v1SfpTemp
				Temperature0c1,
				smc2000c01v1SerialNo
				SerialNo
			 }

		-- 1.3.6.1.4.1.10106.3.101291.1.1.1
		smc2000c01v1Index OBJECT-TYPE
			SYNTAX ModuleIndex
			MAX-ACCESS read-only
			STATUS current
			DESCRIPTION
				"Index of SMC2000C01V1 Table"
		::= { smc2000c01v1Entry 1 }

		-- 1.3.6.1.4.1.10106.3.101291.1.1.3
		smc2000c01v1P1EthMode OBJECT-TYPE
			SYNTAX EthMode2000
			MAX-ACCESS read-write
			STATUS current
			DESCRIPTION
				"Ethernet mode in Port 1"
		::= { smc2000c01v1Entry 3 }

		-- 1.3.6.1.4.1.10106.3.101291.1.1.5
		smc2000c01v1P2EthMode OBJECT-TYPE
			SYNTAX EthMode2000
			MAX-ACCESS read-write
			STATUS current
			DESCRIPTION
				"Ethernet mode in Port 2"
		::= { smc2000c01v1Entry 5 }

		-- 1.3.6.1.4.1.10106.3.101291.1.1.7
		smc2000c01v1PoEthMode OBJECT-TYPE
			SYNTAX EthMode2g5
			MAX-ACCESS read-write
			STATUS current
			DESCRIPTION
				"Ethernet mode in Optical port"
		::= { smc2000c01v1Entry 7 }

		-- 1.3.6.1.4.1.10106.3.101291.1.1.9
		smc2000c01v1SfpPres OBJECT-TYPE
			SYNTAX BitFailN
			MAX-ACCESS read-only
			STATUS current
			DESCRIPTION
				"SFP module present"
		::= { smc2000c01v1Entry 9 }

		-- 1.3.6.1.4.1.10106.3.101291.1.1.10
		smc2000c01v1SfpPresTrapEnable OBJECT-TYPE
			SYNTAX AlarmEnable
			MAX-ACCESS read-write
			STATUS current
			DESCRIPTION
				"SFP module present Trap Enable"
		::= { smc2000c01v1Entry 10 }

		-- 1.3.6.1.4.1.10106.3.101291.1.1.11
		smc2000c01v1SfpFail OBJECT-TYPE
			SYNTAX BitFail
			MAX-ACCESS read-only
			STATUS current
			DESCRIPTION
				"Indicates a laser fault"
		::= { smc2000c01v1Entry 11 }

		-- 1.3.6.1.4.1.10106.3.101291.1.1.12
		smc2000c01v1SfpFailTrapEnable OBJECT-TYPE
			SYNTAX AlarmEnable
			MAX-ACCESS read-write
			STATUS current
			DESCRIPTION
				"Indicates a laser fault Trap Enable"
		::= { smc2000c01v1Entry 12 }

		-- 1.3.6.1.4.1.10106.3.101291.1.1.13
		smc2000c01v1SfpLos OBJECT-TYPE
			SYNTAX BitFail
			MAX-ACCESS read-only
			STATUS current
			DESCRIPTION
				"SFP loss of signal"
		::= { smc2000c01v1Entry 13 }

		-- 1.3.6.1.4.1.10106.3.101291.1.1.14
		smc2000c01v1SfpLosTrapEnable OBJECT-TYPE
			SYNTAX AlarmEnable
			MAX-ACCESS read-write
			STATUS current
			DESCRIPTION
				"SFP loss of signal Trap Enable"
		::= { smc2000c01v1Entry 14 }

		-- 1.3.6.1.4.1.10106.3.101291.1.1.15
		smc2000c01v1SfpDiagSupport OBJECT-TYPE
			SYNTAX BitFailN
			MAX-ACCESS read-only
			STATUS current
			DESCRIPTION
				"SFP mod. supports diagnostics"
		::= { smc2000c01v1Entry 15 }

		-- 1.3.6.1.4.1.10106.3.101291.1.1.17
		smc2000c01v1P1Status OBJECT-TYPE
			SYNTAX Smc2EthModeSt
			MAX-ACCESS read-only
			STATUS current
			DESCRIPTION
				"Ethernet connection status in Port 1"
		::= { smc2000c01v1Entry 17 }

		-- 1.3.6.1.4.1.10106.3.101291.1.1.18
		smc2000c01v1P1StatusTrapEnable OBJECT-TYPE
			SYNTAX AlarmEnable
			MAX-ACCESS read-write
			STATUS current
			DESCRIPTION
				"Ethernet connection status in Port 1 Trap Enable"
		::= { smc2000c01v1Entry 18 }

		-- 1.3.6.1.4.1.10106.3.101291.1.1.19
		smc2000c01v1P2Status OBJECT-TYPE
			SYNTAX Smc2EthModeSt
			MAX-ACCESS read-only
			STATUS current
			DESCRIPTION
				"Ethernet connection status in Port 2"
		::= { smc2000c01v1Entry 19 }

		-- 1.3.6.1.4.1.10106.3.101291.1.1.20
		smc2000c01v1P2StatusTrapEnable OBJECT-TYPE
			SYNTAX AlarmEnable
			MAX-ACCESS read-write
			STATUS current
			DESCRIPTION
				"Ethernet connection status in Port 2 Trap Enable"
		::= { smc2000c01v1Entry 20 }

		-- 1.3.6.1.4.1.10106.3.101291.1.1.21
		smc2000c01v1PoStatus OBJECT-TYPE
			SYNTAX Smc2EthModeSt
			MAX-ACCESS read-only
			STATUS current
			DESCRIPTION
				"Ethernet connection status in Optical Port"
		::= { smc2000c01v1Entry 21 }

		-- 1.3.6.1.4.1.10106.3.101291.1.1.22
		smc2000c01v1PoStatusTrapEnable OBJECT-TYPE
			SYNTAX AlarmEnable
			MAX-ACCESS read-write
			STATUS current
			DESCRIPTION
				"Ethernet connection status in Optical Port Trap Enable"
		::= { smc2000c01v1Entry 22 }

		-- 1.3.6.1.4.1.10106.3.101291.1.1.23
		smc2000c01v1SfpPower OBJECT-TYPE
			SYNTAX OptPowerX2Uw
			MAX-ACCESS read-only
			STATUS current
			DESCRIPTION
				"Optical received power"
		::= { smc2000c01v1Entry 23 }

		-- 1.3.6.1.4.1.10106.3.101291.1.1.25
		smc2000c01v1SfpTemp OBJECT-TYPE
			SYNTAX Temperature0c1
			MAX-ACCESS read-only
			STATUS current
			DESCRIPTION
				"SFP module temperatura"
		::= { smc2000c01v1Entry 25 }

		-- 1.3.6.1.4.1.10106.3.101291.1.1.27
		smc2000c01v1SerialNo OBJECT-TYPE
			SYNTAX SerialNo
			MAX-ACCESS read-only
			STATUS current
			DESCRIPTION
				"Serial number"
		::= { smc2000c01v1Entry 27 }

		-- 1.3.6.1.4.1.10106.3.517501
		gps2000c01v1 OBJECT IDENTIFIER ::= { albalaProducts 517501 }

		-- 1.3.6.1.4.1.10106.3.517501.1
		gps2000c01v1Table  OBJECT-TYPE
			SYNTAX SEQUENCE OF Gps2000c01v1Entry
			MAX-ACCESS not-accessible
			STATUS current
			DESCRIPTION
				"Module  GPS2000C01V1 Table"
			::= { gps2000c01v1 1 }

		-- 1.3.6.1.4.1.10106.3.517501.1.1
		gps2000c01v1Entry  OBJECT-TYPE
			SYNTAX Gps2000c01v1Entry
			MAX-ACCESS not-accessible
			STATUS current
			DESCRIPTION
				"Module GPS2000C01V1 Entry"
			INDEX { gps2000c01v1Index }
			::= { gps2000c01v1Table 1 }

			Gps2000c01v1Entry ::=
			SEQUENCE {
				gps2000c01v1Index
				ModuleIndex,
				gps2000c01v1SyncMode
				Gps2SyncMode,
				gps2000c01v1PtpSrvEnable
				Bit0No1Yes,
				gps2000c01v1PtpCliEnable
				Bit0No1Yes,
				gps2000c01v1InfoTimePps
				Bit0No1Yes,
				gps2000c01v1CableDelay
				DelayX1Ns,
				gps2000c01v1PtpDelayAsym
				TimeX1Ns,
				gps2000c01v1HoldoverTout
				GpsHoldovrTime,
				gps2000c01v1FTimeDriftEst
				Gps2FrqTimDrf,
				gps2000c01v1FTempDriftEst
				Gps2FrqTemDrf,
				gps2000c01v1Longitude
				AngleDeg1,
				gps2000c01v1Latitude
				AngleDeg1,
				gps2000c01v1Altitude
				AltitudeM1,
				gps2000c01v1IpAdd0
				Uint8,
				gps2000c01v1IpAdd1
				Uint8,
				gps2000c01v1IpAdd2
				Uint8,
				gps2000c01v1IpAdd3
				Uint8,
				gps2000c01v1IpMask0
				Uint8,
				gps2000c01v1IpMask1
				Uint8,
				gps2000c01v1IpMask2
				Uint8,
				gps2000c01v1IpMask3
				Uint8,
				gps2000c01v1IpGway0
				Uint8,
				gps2000c01v1IpGway1
				Uint8,
				gps2000c01v1IpGway2
				Uint8,
				gps2000c01v1IpGway3
				Uint8,
				gps2000c01v1Profile
				PtpProfile,
				gps2000c01v1DelayMechanism
				PtpDelayMech,
				gps2000c01v1Priority1
				Uint8,
				gps2000c01v1Priority2
				Uint8,
				gps2000c01v1DomainNumber
				Uint8,
				gps2000c01v1LogAnnounceInt
				PtpInterval,
				gps2000c01v1LogSyncInt
				PtpInterval,
				gps2000c01v1LogMinDRInt
				PtpInterval,
				gps2000c01v1LogMinPdRInt
				PtpInterval,
				gps2000c01v1AnnounceRTout
				Uint4,
				gps2000c01v1ClockClass
				Uint8,
				gps2000c01v1PtpState
				PtpState,
				gps2000c01v1GnssLos
				BitFail,
				gps2000c01v1GnssLosTrapEnable
				AlarmEnable,
				gps2000c01v1GnssPpsLos
				BitFail,
				gps2000c01v1GnssPpsLosTrapEnable
				AlarmEnable,
				gps2000c01v1GnssUnlock
				BitFail,
				gps2000c01v1GnssUnlockTrapEnable
				AlarmEnable,
				gps2000c01v1GnssPpsErr
				BitFail,
				gps2000c01v1GnssPpsErrTrapEnable
				AlarmEnable,
				gps2000c01v1PtpLos
				BitFail,
				gps2000c01v1PtpLosTrapEnable
				AlarmEnable,
				gps2000c01v1PtpPpsLos
				BitFail,
				gps2000c01v1PtpPpsLosTrapEnable
				AlarmEnable,
				gps2000c01v1PtpUnlock
				BitFail,
				gps2000c01v1PtpUnlockTrapEnable
				AlarmEnable,
				gps2000c01v1PtpPpsErr
				BitFail,
				gps2000c01v1PtpPpsErrTrapEnable
				AlarmEnable,
				gps2000c01v1SyncState
				Gps2SyncState,
				gps2000c01v1SyncStateTrapEnable
				AlarmEnable,
				gps2000c01v1ValidPps
				Bit0No1Yes,
				gps2000c01v1ValidPpsTrapEnable
				AlarmEnable,
				gps2000c01v1ModuleActive
				Bit0No1Yes,
				gps2000c01v1ModuleActiveTrapEnable
				AlarmEnable,
				gps2000c01v1RedSyncState
				Gps2SyncState,
				gps2000c01v1RedSyncStateTrapEnable
				AlarmEnable,
				gps2000c01v1RedModule
				Bit0No1Yes,
				gps2000c01v1RedModuleTrapEnable
				AlarmEnable,
				gps2000c01v1FixMode
				Gps2FixMode,
				gps2000c01v1FixModeTrapEnable
				AlarmEnable,
				gps2000c01v1DiffMode
				Bit0No1Yes,
				gps2000c01v1NumUsedSats
				Uint8,
				gps2000c01v1CN0Max
				LevelDbHz,
				gps2000c01v1PositionAcc
				AltitudeM1,
				gps2000c01v1TimTosOffset
				TimeX1Ns,
				gps2000c01v1SurveyTout
				TimeS2,
				gps2000c01v1HoldoverTime
				GpsHoldovrTime,
				gps2000c01v1PowerStat
				Bit0Ok1Fail,
				gps2000c01v1PowerStatTrapEnable
				AlarmEnable,
				gps2000c01v1AntennaStat
				GpsAntenaStat,
				gps2000c01v1AntennaStatTrapEnable
				AlarmEnable,
				gps2000c01v1EthLink
				Bit0No1Yes,
				gps2000c01v1EthLinkTrapEnable
				AlarmEnable,
				gps2000c01v1AdjustingFreq
				Bit0No1Yes,
				gps2000c01v1OcxoWarInProg
				Bit0No1Yes,
				gps2000c01v1OnePpsStat
				Bit0Ina1Act,
				gps2000c01v1OnePpsStatTrapEnable
				AlarmEnable,
				gps2000c01v1OnePps
				BitPps,
				gps2000c01v1GnssDelay
				TimeX1p25Ns,
				gps2000c01v1PtpDelay
				TimeX1p25Ns,
				gps2000c01v1SerialNo
				SerialNo,
				gps2000c01v1IpNtpSrv0
				Uint8,
				gps2000c01v1IpNtpSrv1
				Uint8,
				gps2000c01v1IpNtpSrv2
				Uint8,
				gps2000c01v1IpNtpSrv3
				Uint8,
				gps2000c01v1TimeDateOk
				BitFailN
			 }

		-- 1.3.6.1.4.1.10106.3.101291.1.1.1
		gps2000c01v1Index OBJECT-TYPE
			SYNTAX ModuleIndex
			MAX-ACCESS read-only
			STATUS current
			DESCRIPTION
				"Index of GPS2000C01V1 Table"
		::= { gps2000c01v1Entry 1 }

		-- 1.3.6.1.4.1.10106.3.101291.1.1.3
		gps2000c01v1SyncMode OBJECT-TYPE
			SYNTAX Gps2SyncMode
			MAX-ACCESS read-write
			STATUS current
			DESCRIPTION
				"Allows selecting the synchronization mode"
		::= { gps2000c01v1Entry 3 }

		-- 1.3.6.1.4.1.10106.3.101291.1.1.5
		gps2000c01v1PtpSrvEnable OBJECT-TYPE
			SYNTAX Bit0No1Yes
			MAX-ACCESS read-write
			STATUS current
			DESCRIPTION
				"Allows enabling the PTP server when Sync mode is GNSS"
		::= { gps2000c01v1Entry 5 }

		-- 1.3.6.1.4.1.10106.3.101291.1.1.7
		gps2000c01v1PtpCliEnable OBJECT-TYPE
			SYNTAX Bit0No1Yes
			MAX-ACCESS read-write
			STATUS current
			DESCRIPTION
				"Allows enabling the PTP client for logging when Sync mode is GNSS"
		::= { gps2000c01v1Entry 7 }

		-- 1.3.6.1.4.1.10106.3.101291.1.1.9
		gps2000c01v1InfoTimePps OBJECT-TYPE
			SYNTAX Bit0No1Yes
			MAX-ACCESS read-write
			STATUS current
			DESCRIPTION
				"Allows embedding PTP timestamp in 1 PPS signal"
		::= { gps2000c01v1Entry 9 }

		-- 1.3.6.1.4.1.10106.3.101291.1.1.11
		gps2000c01v1CableDelay OBJECT-TYPE
			SYNTAX DelayX1Ns
			MAX-ACCESS read-write
			STATUS current
			DESCRIPTION
				"Allows compensating the antenna cable delay"
		::= { gps2000c01v1Entry 11 }

		-- 1.3.6.1.4.1.10106.3.101291.1.1.13
		gps2000c01v1PtpDelayAsym OBJECT-TYPE
			SYNTAX TimeX1Ns
			MAX-ACCESS read-write
			STATUS current
			DESCRIPTION
				"Allows compensating the PTP delay asymmetry"
		::= { gps2000c01v1Entry 13 }

		-- 1.3.6.1.4.1.10106.3.101291.1.1.15
		gps2000c01v1HoldoverTout OBJECT-TYPE
			SYNTAX GpsHoldovrTime
			MAX-ACCESS read-write
			STATUS current
			DESCRIPTION
				"Allows selecting the maximum holdover time"
		::= { gps2000c01v1Entry 15 }

		-- 1.3.6.1.4.1.10106.3.101291.1.1.17
		gps2000c01v1FTimeDriftEst OBJECT-TYPE
			SYNTAX Gps2FrqTimDrf
			MAX-ACCESS read-only
			STATUS current
			DESCRIPTION
				"Frequency time drift estimation"
		::= { gps2000c01v1Entry 17 }

		-- 1.3.6.1.4.1.10106.3.101291.1.1.19
		gps2000c01v1FTempDriftEst OBJECT-TYPE
			SYNTAX Gps2FrqTemDrf
			MAX-ACCESS read-only
			STATUS current
			DESCRIPTION
				"Frequency temperature drift estimation"
		::= { gps2000c01v1Entry 19 }

		-- 1.3.6.1.4.1.10106.3.101291.1.1.21
		gps2000c01v1Longitude OBJECT-TYPE
			SYNTAX AngleDeg1
			MAX-ACCESS read-only
			STATUS current
			DESCRIPTION
				"GNSS receiver reported longitude"
		::= { gps2000c01v1Entry 21 }

		-- 1.3.6.1.4.1.10106.3.101291.1.1.23
		gps2000c01v1Latitude OBJECT-TYPE
			SYNTAX AngleDeg1
			MAX-ACCESS read-only
			STATUS current
			DESCRIPTION
				"GNSS receiver reported latitude"
		::= { gps2000c01v1Entry 23 }

		-- 1.3.6.1.4.1.10106.3.101291.1.1.25
		gps2000c01v1Altitude OBJECT-TYPE
			SYNTAX AltitudeM1
			MAX-ACCESS read-only
			STATUS current
			DESCRIPTION
				"GNSS receiver reported altitude"
		::= { gps2000c01v1Entry 25 }

		-- 1.3.6.1.4.1.10106.3.101291.1.1.27
		gps2000c01v1IpAdd0 OBJECT-TYPE
			SYNTAX Uint8
			MAX-ACCESS read-write
			STATUS current
			DESCRIPTION
				"Unicast IP address (0)"
		::= { gps2000c01v1Entry 27 }

		-- 1.3.6.1.4.1.10106.3.101291.1.1.29
		gps2000c01v1IpAdd1 OBJECT-TYPE
			SYNTAX Uint8
			MAX-ACCESS read-write
			STATUS current
			DESCRIPTION
				"Unicast IP address (1)"
		::= { gps2000c01v1Entry 29 }

		-- 1.3.6.1.4.1.10106.3.101291.1.1.31
		gps2000c01v1IpAdd2 OBJECT-TYPE
			SYNTAX Uint8
			MAX-ACCESS read-write
			STATUS current
			DESCRIPTION
				"Unicast IP address (2)"
		::= { gps2000c01v1Entry 31 }

		-- 1.3.6.1.4.1.10106.3.101291.1.1.33
		gps2000c01v1IpAdd3 OBJECT-TYPE
			SYNTAX Uint8
			MAX-ACCESS read-write
			STATUS current
			DESCRIPTION
				"Unicast IP address (3)"
		::= { gps2000c01v1Entry 33 }

		-- 1.3.6.1.4.1.10106.3.101291.1.1.35
		gps2000c01v1IpMask0 OBJECT-TYPE
			SYNTAX Uint8
			MAX-ACCESS read-write
			STATUS current
			DESCRIPTION
				"IP mask (0)"
		::= { gps2000c01v1Entry 35 }

		-- 1.3.6.1.4.1.10106.3.101291.1.1.37
		gps2000c01v1IpMask1 OBJECT-TYPE
			SYNTAX Uint8
			MAX-ACCESS read-write
			STATUS current
			DESCRIPTION
				"IP mask (1)"
		::= { gps2000c01v1Entry 37 }

		-- 1.3.6.1.4.1.10106.3.101291.1.1.39
		gps2000c01v1IpMask2 OBJECT-TYPE
			SYNTAX Uint8
			MAX-ACCESS read-write
			STATUS current
			DESCRIPTION
				"IP mask (2)"
		::= { gps2000c01v1Entry 39 }

		-- 1.3.6.1.4.1.10106.3.101291.1.1.41
		gps2000c01v1IpMask3 OBJECT-TYPE
			SYNTAX Uint8
			MAX-ACCESS read-write
			STATUS current
			DESCRIPTION
				"IP mask (3)"
		::= { gps2000c01v1Entry 41 }

		-- 1.3.6.1.4.1.10106.3.101291.1.1.43
		gps2000c01v1IpGway0 OBJECT-TYPE
			SYNTAX Uint8
			MAX-ACCESS read-write
			STATUS current
			DESCRIPTION
				"Gateway IP address (0)"
		::= { gps2000c01v1Entry 43 }

		-- 1.3.6.1.4.1.10106.3.101291.1.1.45
		gps2000c01v1IpGway1 OBJECT-TYPE
			SYNTAX Uint8
			MAX-ACCESS read-write
			STATUS current
			DESCRIPTION
				"Gateway IP address (1)"
		::= { gps2000c01v1Entry 45 }

		-- 1.3.6.1.4.1.10106.3.101291.1.1.47
		gps2000c01v1IpGway2 OBJECT-TYPE
			SYNTAX Uint8
			MAX-ACCESS read-write
			STATUS current
			DESCRIPTION
				"Gateway IP address (2)"
		::= { gps2000c01v1Entry 47 }

		-- 1.3.6.1.4.1.10106.3.101291.1.1.49
		gps2000c01v1IpGway3 OBJECT-TYPE
			SYNTAX Uint8
			MAX-ACCESS read-write
			STATUS current
			DESCRIPTION
				"Gateway IP address (3)"
		::= { gps2000c01v1Entry 49 }

		-- 1.3.6.1.4.1.10106.3.101291.1.1.51
		gps2000c01v1Profile OBJECT-TYPE
			SYNTAX PtpProfile
			MAX-ACCESS read-write
			STATUS current
			DESCRIPTION
				"Allows loading default values of a PTP profile"
		::= { gps2000c01v1Entry 51 }

		-- 1.3.6.1.4.1.10106.3.101291.1.1.53
		gps2000c01v1DelayMechanism OBJECT-TYPE
			SYNTAX PtpDelayMech
			MAX-ACCESS read-write
			STATUS current
			DESCRIPTION
				"Allows selecting the delay mechanism"
		::= { gps2000c01v1Entry 53 }

		-- 1.3.6.1.4.1.10106.3.101291.1.1.55
		gps2000c01v1Priority1 OBJECT-TYPE
			SYNTAX Uint8
			MAX-ACCESS read-write
			STATUS current
			DESCRIPTION
				"Allows selecting the Priority1 attribute of the local clock. It is used in the best master selection algorithm"
		::= { gps2000c01v1Entry 55 }

		-- 1.3.6.1.4.1.10106.3.101291.1.1.57
		gps2000c01v1Priority2 OBJECT-TYPE
			SYNTAX Uint8
			MAX-ACCESS read-write
			STATUS current
			DESCRIPTION
				"Allows selecting the Priority2 attribute of the local clock. It is used in the best master selection algorithm"
		::= { gps2000c01v1Entry 57 }

		-- 1.3.6.1.4.1.10106.3.101291.1.1.59
		gps2000c01v1DomainNumber OBJECT-TYPE
			SYNTAX Uint8
			MAX-ACCESS read-write
			STATUS current
			DESCRIPTION
				"Allows selecting the Domanin number attribute of the local clock"
		::= { gps2000c01v1Entry 59 }

		-- 1.3.6.1.4.1.10106.3.101291.1.1.61
		gps2000c01v1LogAnnounceInt OBJECT-TYPE
			SYNTAX PtpInterval
			MAX-ACCESS read-write
			STATUS current
			DESCRIPTION
				"Allows selecting the mean interval between Announce messages"
		::= { gps2000c01v1Entry 61 }

		-- 1.3.6.1.4.1.10106.3.101291.1.1.63
		gps2000c01v1LogSyncInt OBJECT-TYPE
			SYNTAX PtpInterval
			MAX-ACCESS read-write
			STATUS current
			DESCRIPTION
				"Allows selecting the mean interval between Sync messages"
		::= { gps2000c01v1Entry 63 }

		-- 1.3.6.1.4.1.10106.3.101291.1.1.65
		gps2000c01v1LogMinDRInt OBJECT-TYPE
			SYNTAX PtpInterval
			MAX-ACCESS read-write
			STATUS current
			DESCRIPTION
				"Allows selecting the minimum mean interval between Delay_Req messages"
		::= { gps2000c01v1Entry 65 }

		-- 1.3.6.1.4.1.10106.3.101291.1.1.67
		gps2000c01v1LogMinPdRInt OBJECT-TYPE
			SYNTAX PtpInterval
			MAX-ACCESS read-write
			STATUS current
			DESCRIPTION
				"Allows selecting the minimum mean interval between Pdelay_Req messages"
		::= { gps2000c01v1Entry 67 }

		-- 1.3.6.1.4.1.10106.3.101291.1.1.69
		gps2000c01v1AnnounceRTout OBJECT-TYPE
			SYNTAX Uint4
			MAX-ACCESS read-write
			STATUS current
			DESCRIPTION
				"Allows selecting the number of missed Announce messages before the last Announce messages expires"
		::= { gps2000c01v1Entry 69 }

		-- 1.3.6.1.4.1.10106.3.101291.1.1.71
		gps2000c01v1ClockClass OBJECT-TYPE
			SYNTAX Uint8
			MAX-ACCESS read-only
			STATUS current
			DESCRIPTION
				"Indicates the value of the ClockClass attribute of the local clock"
		::= { gps2000c01v1Entry 71 }

		-- 1.3.6.1.4.1.10106.3.101291.1.1.73
		gps2000c01v1PtpState OBJECT-TYPE
			SYNTAX PtpState
			MAX-ACCESS read-only
			STATUS current
			DESCRIPTION
				"Indicates the PTP state"
		::= { gps2000c01v1Entry 73 }

		-- 1.3.6.1.4.1.10106.3.101291.1.1.75
		gps2000c01v1GnssLos OBJECT-TYPE
			SYNTAX BitFail
			MAX-ACCESS read-only
			STATUS current
			DESCRIPTION
				"GNSS loss of signal. To be cleared it has to be for 30 s in in 3D-FIX or Time mode"
		::= { gps2000c01v1Entry 75 }

		-- 1.3.6.1.4.1.10106.3.101291.1.1.76
		gps2000c01v1GnssLosTrapEnable OBJECT-TYPE
			SYNTAX AlarmEnable
			MAX-ACCESS read-write
			STATUS current
			DESCRIPTION
				"GNSS loss of signal. To be cleared it has to be for 30 s in in 3D-FIX or Time mode Trap Enable"
		::= { gps2000c01v1Entry 76 }

		-- 1.3.6.1.4.1.10106.3.101291.1.1.77
		gps2000c01v1GnssPpsLos OBJECT-TYPE
			SYNTAX BitFail
			MAX-ACCESS read-only
			STATUS current
			DESCRIPTION
				"GNSS loss of PPS. It is cleared when the error of the PPS delivered by GNSS module is less than 5 ns. It is set when the delay is greater than 50 ns"
		::= { gps2000c01v1Entry 77 }

		-- 1.3.6.1.4.1.10106.3.101291.1.1.78
		gps2000c01v1GnssPpsLosTrapEnable OBJECT-TYPE
			SYNTAX AlarmEnable
			MAX-ACCESS read-write
			STATUS current
			DESCRIPTION
				"GNSS loss of PPS. It is cleared when the error of the PPS delivered by GNSS module is less than 5 ns. It is set when the delay is greater than 50 ns Trap Enable"
		::= { gps2000c01v1Entry 78 }

		-- 1.3.6.1.4.1.10106.3.101291.1.1.79
		gps2000c01v1GnssUnlock OBJECT-TYPE
			SYNTAX BitFail
			MAX-ACCESS read-only
			STATUS current
			DESCRIPTION
				"GNSS PPS unlock. It is cleared when the error of the output PPS is less than 10 ns. It is set when the error is greater than 100 ns."
		::= { gps2000c01v1Entry 79 }

		-- 1.3.6.1.4.1.10106.3.101291.1.1.80
		gps2000c01v1GnssUnlockTrapEnable OBJECT-TYPE
			SYNTAX AlarmEnable
			MAX-ACCESS read-write
			STATUS current
			DESCRIPTION
				"GNSS PPS unlock. It is cleared when the error of the output PPS is less than 10 ns. It is set when the error is greater than 100 ns. Trap Enable"
		::= { gps2000c01v1Entry 80 }

		-- 1.3.6.1.4.1.10106.3.101291.1.1.81
		gps2000c01v1GnssPpsErr OBJECT-TYPE
			SYNTAX BitFail
			MAX-ACCESS read-only
			STATUS current
			DESCRIPTION
				"GNSS pulse error. It is cleared when the error of the output PPS is less than the value specified in 'GNSS valid PPS margin'. It is set when the error is greater than this value."
		::= { gps2000c01v1Entry 81 }

		-- 1.3.6.1.4.1.10106.3.101291.1.1.82
		gps2000c01v1GnssPpsErrTrapEnable OBJECT-TYPE
			SYNTAX AlarmEnable
			MAX-ACCESS read-write
			STATUS current
			DESCRIPTION
				"GNSS pulse error. It is cleared when the error of the output PPS is less than the value specified in 'GNSS valid PPS margin'. It is set when the error is greater than this value. Trap Enable"
		::= { gps2000c01v1Entry 82 }

		-- 1.3.6.1.4.1.10106.3.101291.1.1.83
		gps2000c01v1PtpLos OBJECT-TYPE
			SYNTAX BitFail
			MAX-ACCESS read-only
			STATUS current
			DESCRIPTION
				"PTP loss of signal.It is cleared when the PTP module is in Slave or Uncalibrated mode"
		::= { gps2000c01v1Entry 83 }

		-- 1.3.6.1.4.1.10106.3.101291.1.1.84
		gps2000c01v1PtpLosTrapEnable OBJECT-TYPE
			SYNTAX AlarmEnable
			MAX-ACCESS read-write
			STATUS current
			DESCRIPTION
				"PTP loss of signal.It is cleared when the PTP module is in Slave or Uncalibrated mode Trap Enable"
		::= { gps2000c01v1Entry 84 }

		-- 1.3.6.1.4.1.10106.3.101291.1.1.85
		gps2000c01v1PtpPpsLos OBJECT-TYPE
			SYNTAX BitFail
			MAX-ACCESS read-only
			STATUS current
			DESCRIPTION
				"PTP loss of PPS. It is cleared after 30 s receiving a valid PPS from PTP module"
		::= { gps2000c01v1Entry 85 }

		-- 1.3.6.1.4.1.10106.3.101291.1.1.86
		gps2000c01v1PtpPpsLosTrapEnable OBJECT-TYPE
			SYNTAX AlarmEnable
			MAX-ACCESS read-write
			STATUS current
			DESCRIPTION
				"PTP loss of PPS. It is cleared after 30 s receiving a valid PPS from PTP module Trap Enable"
		::= { gps2000c01v1Entry 86 }

		-- 1.3.6.1.4.1.10106.3.101291.1.1.87
		gps2000c01v1PtpUnlock OBJECT-TYPE
			SYNTAX BitFail
			MAX-ACCESS read-only
			STATUS current
			DESCRIPTION
				"PTP PPS unlock. It is cleared when the error of the output PPS is less than 25 ns. It is set when the error is greater than 250 ns."
		::= { gps2000c01v1Entry 87 }

		-- 1.3.6.1.4.1.10106.3.101291.1.1.88
		gps2000c01v1PtpUnlockTrapEnable OBJECT-TYPE
			SYNTAX AlarmEnable
			MAX-ACCESS read-write
			STATUS current
			DESCRIPTION
				"PTP PPS unlock. It is cleared when the error of the output PPS is less than 25 ns. It is set when the error is greater than 250 ns. Trap Enable"
		::= { gps2000c01v1Entry 88 }

		-- 1.3.6.1.4.1.10106.3.101291.1.1.89
		gps2000c01v1PtpPpsErr OBJECT-TYPE
			SYNTAX BitFail
			MAX-ACCESS read-only
			STATUS current
			DESCRIPTION
				"PTP PPS error. It is cleared when the error of the output PPS is less than the value specified in 'PTP valid PPS margin'. It is set when the error is greater than this value."
		::= { gps2000c01v1Entry 89 }

		-- 1.3.6.1.4.1.10106.3.101291.1.1.90
		gps2000c01v1PtpPpsErrTrapEnable OBJECT-TYPE
			SYNTAX AlarmEnable
			MAX-ACCESS read-write
			STATUS current
			DESCRIPTION
				"PTP PPS error. It is cleared when the error of the output PPS is less than the value specified in 'PTP valid PPS margin'. It is set when the error is greater than this value. Trap Enable"
		::= { gps2000c01v1Entry 90 }

		-- 1.3.6.1.4.1.10106.3.101291.1.1.91
		gps2000c01v1SyncState OBJECT-TYPE
			SYNTAX Gps2SyncState
			MAX-ACCESS read-only
			STATUS current
			DESCRIPTION
				"Indicates the synchronization state"
		::= { gps2000c01v1Entry 91 }

		-- 1.3.6.1.4.1.10106.3.101291.1.1.92
		gps2000c01v1SyncStateTrapEnable OBJECT-TYPE
			SYNTAX AlarmEnable
			MAX-ACCESS read-write
			STATUS current
			DESCRIPTION
				"Indicates the synchronization state Trap Enable"
		::= { gps2000c01v1Entry 92 }

		-- 1.3.6.1.4.1.10106.3.101291.1.1.93
		gps2000c01v1ValidPps OBJECT-TYPE
			SYNTAX Bit0No1Yes
			MAX-ACCESS read-only
			STATUS current
			DESCRIPTION
				"Indicates that the internally generated PPS signal has been phase aligned with an external reference (GNSS or PTP)"
		::= { gps2000c01v1Entry 93 }

		-- 1.3.6.1.4.1.10106.3.101291.1.1.94
		gps2000c01v1ValidPpsTrapEnable OBJECT-TYPE
			SYNTAX AlarmEnable
			MAX-ACCESS read-write
			STATUS current
			DESCRIPTION
				"Indicates that the internally generated PPS signal has been phase aligned with an external reference (GNSS or PTP) Trap Enable"
		::= { gps2000c01v1Entry 94 }

		-- 1.3.6.1.4.1.10106.3.101291.1.1.95
		gps2000c01v1ModuleActive OBJECT-TYPE
			SYNTAX Bit0No1Yes
			MAX-ACCESS read-only
			STATUS current
			DESCRIPTION
				"Indicates that this module is the one that provides the reference signals"
		::= { gps2000c01v1Entry 95 }

		-- 1.3.6.1.4.1.10106.3.101291.1.1.96
		gps2000c01v1ModuleActiveTrapEnable OBJECT-TYPE
			SYNTAX AlarmEnable
			MAX-ACCESS read-write
			STATUS current
			DESCRIPTION
				"Indicates that this module is the one that provides the reference signals Trap Enable"
		::= { gps2000c01v1Entry 96 }

		-- 1.3.6.1.4.1.10106.3.101291.1.1.97
		gps2000c01v1RedSyncState OBJECT-TYPE
			SYNTAX Gps2SyncState
			MAX-ACCESS read-only
			STATUS current
			DESCRIPTION
				"Indicates the redundant module's synchronization state"
		::= { gps2000c01v1Entry 97 }

		-- 1.3.6.1.4.1.10106.3.101291.1.1.98
		gps2000c01v1RedSyncStateTrapEnable OBJECT-TYPE
			SYNTAX AlarmEnable
			MAX-ACCESS read-write
			STATUS current
			DESCRIPTION
				"Indicates the redundant module's synchronization state Trap Enable"
		::= { gps2000c01v1Entry 98 }

		-- 1.3.6.1.4.1.10106.3.101291.1.1.99
		gps2000c01v1RedModule OBJECT-TYPE
			SYNTAX Bit0No1Yes
			MAX-ACCESS read-only
			STATUS current
			DESCRIPTION
				"Indicates if the redundant module is present"
		::= { gps2000c01v1Entry 99 }

		-- 1.3.6.1.4.1.10106.3.101291.1.1.100
		gps2000c01v1RedModuleTrapEnable OBJECT-TYPE
			SYNTAX AlarmEnable
			MAX-ACCESS read-write
			STATUS current
			DESCRIPTION
				"Indicates if the redundant module is present Trap Enable"
		::= { gps2000c01v1Entry 100 }

		-- 1.3.6.1.4.1.10106.3.101291.1.1.101
		gps2000c01v1FixMode OBJECT-TYPE
			SYNTAX Gps2FixMode
			MAX-ACCESS read-only
			STATUS current
			DESCRIPTION
				"GNSS receiver module satellite tracking mode"
		::= { gps2000c01v1Entry 101 }

		-- 1.3.6.1.4.1.10106.3.101291.1.1.102
		gps2000c01v1FixModeTrapEnable OBJECT-TYPE
			SYNTAX AlarmEnable
			MAX-ACCESS read-write
			STATUS current
			DESCRIPTION
				"GNSS receiver module satellite tracking mode Trap Enable"
		::= { gps2000c01v1Entry 102 }

		-- 1.3.6.1.4.1.10106.3.101291.1.1.103
		gps2000c01v1DiffMode OBJECT-TYPE
			SYNTAX Bit0No1Yes
			MAX-ACCESS read-only
			STATUS current
			DESCRIPTION
				"GNSS receiver receives correction data and uses them to improve provided solution"
		::= { gps2000c01v1Entry 103 }

		-- 1.3.6.1.4.1.10106.3.101291.1.1.105
		gps2000c01v1NumUsedSats OBJECT-TYPE
			SYNTAX Uint8
			MAX-ACCESS read-only
			STATUS current
			DESCRIPTION
				"Number of GNSS used in current fix"
		::= { gps2000c01v1Entry 105 }

		-- 1.3.6.1.4.1.10106.3.101291.1.1.107
		gps2000c01v1CN0Max OBJECT-TYPE
			SYNTAX LevelDbHz
			MAX-ACCESS read-only
			STATUS current
			DESCRIPTION
				"Estimated carrier to noise ratio for the best satellite in tracking"
		::= { gps2000c01v1Entry 107 }

		-- 1.3.6.1.4.1.10106.3.101291.1.1.109
		gps2000c01v1PositionAcc OBJECT-TYPE
			SYNTAX AltitudeM1
			MAX-ACCESS read-only
			STATUS current
			DESCRIPTION
				"Estimated position accuracy"
		::= { gps2000c01v1Entry 109 }

		-- 1.3.6.1.4.1.10106.3.101291.1.1.111
		gps2000c01v1TimTosOffset OBJECT-TYPE
			SYNTAX TimeX1Ns
			MAX-ACCESS read-only
			STATUS current
			DESCRIPTION
				"Estimated GNSS module PPS error"
		::= { gps2000c01v1Entry 111 }

		-- 1.3.6.1.4.1.10106.3.101291.1.1.113
		gps2000c01v1SurveyTout OBJECT-TYPE
			SYNTAX TimeS2
			MAX-ACCESS read-only
			STATUS current
			DESCRIPTION
				"Time to exit Survey-in"
		::= { gps2000c01v1Entry 113 }

		-- 1.3.6.1.4.1.10106.3.101291.1.1.115
		gps2000c01v1HoldoverTime OBJECT-TYPE
			SYNTAX GpsHoldovrTime
			MAX-ACCESS read-only
			STATUS current
			DESCRIPTION
				"Holdover time"
		::= { gps2000c01v1Entry 115 }

		-- 1.3.6.1.4.1.10106.3.101291.1.1.117
		gps2000c01v1PowerStat OBJECT-TYPE
			SYNTAX Bit0Ok1Fail
			MAX-ACCESS read-only
			STATUS current
			DESCRIPTION
				"Indicates the power supply status"
		::= { gps2000c01v1Entry 117 }

		-- 1.3.6.1.4.1.10106.3.101291.1.1.118
		gps2000c01v1PowerStatTrapEnable OBJECT-TYPE
			SYNTAX AlarmEnable
			MAX-ACCESS read-write
			STATUS current
			DESCRIPTION
				"Indicates the power supply status Trap Enable"
		::= { gps2000c01v1Entry 118 }

		-- 1.3.6.1.4.1.10106.3.101291.1.1.119
		gps2000c01v1AntennaStat OBJECT-TYPE
			SYNTAX GpsAntenaStat
			MAX-ACCESS read-only
			STATUS current
			DESCRIPTION
				"Indicates the antenna connection status"
		::= { gps2000c01v1Entry 119 }

		-- 1.3.6.1.4.1.10106.3.101291.1.1.120
		gps2000c01v1AntennaStatTrapEnable OBJECT-TYPE
			SYNTAX AlarmEnable
			MAX-ACCESS read-write
			STATUS current
			DESCRIPTION
				"Indicates the antenna connection status Trap Enable"
		::= { gps2000c01v1Entry 120 }

		-- 1.3.6.1.4.1.10106.3.101291.1.1.121
		gps2000c01v1EthLink OBJECT-TYPE
			SYNTAX Bit0No1Yes
			MAX-ACCESS read-only
			STATUS current
			DESCRIPTION
				"Indicates that the Ethernet link is OK"
		::= { gps2000c01v1Entry 121 }

		-- 1.3.6.1.4.1.10106.3.101291.1.1.122
		gps2000c01v1EthLinkTrapEnable OBJECT-TYPE
			SYNTAX AlarmEnable
			MAX-ACCESS read-write
			STATUS current
			DESCRIPTION
				"Indicates that the Ethernet link is OK Trap Enable"
		::= { gps2000c01v1Entry 122 }

		-- 1.3.6.1.4.1.10106.3.101291.1.1.123
		gps2000c01v1AdjustingFreq OBJECT-TYPE
			SYNTAX Bit0No1Yes
			MAX-ACCESS read-only
			STATUS current
			DESCRIPTION
				"Indicates that the module is adjusting the frequency"
		::= { gps2000c01v1Entry 123 }

		-- 1.3.6.1.4.1.10106.3.101291.1.1.125
		gps2000c01v1OcxoWarInProg OBJECT-TYPE
			SYNTAX Bit0No1Yes
			MAX-ACCESS read-only
			STATUS current
			DESCRIPTION
				"Indicates that the OCXO warming is in progress"
		::= { gps2000c01v1Entry 125 }

		-- 1.3.6.1.4.1.10106.3.101291.1.1.127
		gps2000c01v1OnePpsStat OBJECT-TYPE
			SYNTAX Bit0Ina1Act
			MAX-ACCESS read-only
			STATUS current
			DESCRIPTION
				"Indicates that the module is delivering a valid PPS"
		::= { gps2000c01v1Entry 127 }

		-- 1.3.6.1.4.1.10106.3.101291.1.1.128
		gps2000c01v1OnePpsStatTrapEnable OBJECT-TYPE
			SYNTAX AlarmEnable
			MAX-ACCESS read-write
			STATUS current
			DESCRIPTION
				"Indicates that the module is delivering a valid PPS Trap Enable"
		::= { gps2000c01v1Entry 128 }

		-- 1.3.6.1.4.1.10106.3.101291.1.1.129
		gps2000c01v1OnePps OBJECT-TYPE
			SYNTAX BitPps
			MAX-ACCESS read-only
			STATUS current
			DESCRIPTION
				"One pulse per second signal"
		::= { gps2000c01v1Entry 129 }

		-- 1.3.6.1.4.1.10106.3.101291.1.1.131
		gps2000c01v1GnssDelay OBJECT-TYPE
			SYNTAX TimeX1p25Ns
			MAX-ACCESS read-only
			STATUS current
			DESCRIPTION
				"PPS delay relative to GNSS"
		::= { gps2000c01v1Entry 131 }

		-- 1.3.6.1.4.1.10106.3.101291.1.1.133
		gps2000c01v1PtpDelay OBJECT-TYPE
			SYNTAX TimeX1p25Ns
			MAX-ACCESS read-only
			STATUS current
			DESCRIPTION
				"PPS delay relative to PTP"
		::= { gps2000c01v1Entry 133 }

		-- 1.3.6.1.4.1.10106.3.101291.1.1.135
		gps2000c01v1SerialNo OBJECT-TYPE
			SYNTAX SerialNo
			MAX-ACCESS read-only
			STATUS current
			DESCRIPTION
				"Serial number"
		::= { gps2000c01v1Entry 135 }

		-- 1.3.6.1.4.1.10106.3.101291.1.1.137
		gps2000c01v1IpNtpSrv0 OBJECT-TYPE
			SYNTAX Uint8
			MAX-ACCESS read-write
			STATUS current
			DESCRIPTION
				"NTP server IP address (0)"
		::= { gps2000c01v1Entry 137 }

		-- 1.3.6.1.4.1.10106.3.101291.1.1.139
		gps2000c01v1IpNtpSrv1 OBJECT-TYPE
			SYNTAX Uint8
			MAX-ACCESS read-write
			STATUS current
			DESCRIPTION
				"NTP server IP address (1)"
		::= { gps2000c01v1Entry 139 }

		-- 1.3.6.1.4.1.10106.3.101291.1.1.141
		gps2000c01v1IpNtpSrv2 OBJECT-TYPE
			SYNTAX Uint8
			MAX-ACCESS read-write
			STATUS current
			DESCRIPTION
				"NTP server IP address (2)"
		::= { gps2000c01v1Entry 141 }

		-- 1.3.6.1.4.1.10106.3.101291.1.1.143
		gps2000c01v1IpNtpSrv3 OBJECT-TYPE
			SYNTAX Uint8
			MAX-ACCESS read-write
			STATUS current
			DESCRIPTION
				"NTP server IP address (3)"
		::= { gps2000c01v1Entry 143 }

		-- 1.3.6.1.4.1.10106.3.101291.1.1.145
		gps2000c01v1TimeDateOk OBJECT-TYPE
			SYNTAX BitFailN
			MAX-ACCESS read-only
			STATUS current
			DESCRIPTION
				"Time and date OK"
		::= { gps2000c01v1Entry 145 }

		-- 1.3.6.1.4.1.10106.3.520301
		isw3000c01v1 OBJECT IDENTIFIER ::= { albalaProducts 520301 }

		-- 1.3.6.1.4.1.10106.3.520301.1
		isw3000c01v1Table  OBJECT-TYPE
			SYNTAX SEQUENCE OF Isw3000c01v1Entry
			MAX-ACCESS not-accessible
			STATUS current
			DESCRIPTION
				"Module  ISW3000C01V1 Table"
			::= { isw3000c01v1 1 }

		-- 1.3.6.1.4.1.10106.3.520301.1.1
		isw3000c01v1Entry  OBJECT-TYPE
			SYNTAX Isw3000c01v1Entry
			MAX-ACCESS not-accessible
			STATUS current
			DESCRIPTION
				"Module ISW3000C01V1 Entry"
			INDEX { isw3000c01v1Index }
			::= { isw3000c01v1Table 1 }

			Isw3000c01v1Entry ::=
			SEQUENCE {
				isw3000c01v1Index
				ModuleIndex,
				isw3000c01v1Mode
				ChgOverMode2,
				isw3000c01v1ModeTrapEnable
				AlarmEnable,
				isw3000c01v1DvbTMode
				DvbTModeIsw,
				isw3000c01v1DvbTModeTrapEnable
				AlarmEnable,
				isw3000c01v1NarrowPllBw
				Bit0No1Yes,
				isw3000c01v1Buzzer
				BitMask,
				isw3000c01v1NullPckRtp
				Bit0No1Yes,
				isw3000c01v1EnSeamNondvbt
				Bit0No1Yes,
				isw3000c01v1Input
				ChgOverIn2T,
				isw3000c01v1InputTrapEnable
				AlarmEnable,
				isw3000c01v1InputStChange
				Bit0No1Yes,
				isw3000c01v1InputChange
				Bit0No1Yes,
				isw3000c01v1OutDelay
				DelayX100Ns,
				isw3000c01v1OutDelayTrapEnable
				AlarmEnable,
				isw3000c01v1AsiMainPrior
				Uint1,
				isw3000c01v1AsiMainPriorTrapEnable
				AlarmEnable,
				isw3000c01v1AsiResPrior
				Uint1,
				isw3000c01v1AsiResPriorTrapEnable
				AlarmEnable,
				isw3000c01v1StatReset
				Bit0No1Yes,
				isw3000c01v1StatSel
				Bit0Ipm1Ipr,
				isw3000c01v1StatMode
				Bit01s1Total,
				isw3000c01v1IgmpVersion
				Bit0V21V3,
				isw3000c01v1EthMode
				EthMode,
				isw3000c01v1PingEnable
				Bit0No1Yes,
				isw3000c01v1PacketDelay
				DelayPacket2,
				isw3000c01v1PacketDelayTrapEnable
				AlarmEnable,
				isw3000c01v1IpLinkFailEn
				Bit0No1Yes,
				isw3000c01v1IpDestFailEn
				Bit0No1Yes,
				isw3000c01v1TsSyncLossEn
				Bit0No1Yes,
				isw3000c01v1SyncByErrorEn
				Bit0No1Yes,
				isw3000c01v1PatErrorEn
				Bit0No1Yes,
				isw3000c01v1CcErrorEn
				Bit0No1Yes,
				isw3000c01v1PmtErrorEn
				Bit0No1Yes,
				isw3000c01v1PidErrorEn
				Bit0No1Yes,
				isw3000c01v1PidErrorTime
				TimeX1Ms1,
				isw3000c01v1Ch1Selection
				IswChSelection,
				isw3000c01v1Ch1SelectionTrapEnable
				AlarmEnable,
				isw3000c01v1Ch2Selection
				IswChSelection,
				isw3000c01v1Ch2SelectionTrapEnable
				AlarmEnable,
				isw3000c01v1OutDelay0
				DelayX1S127,
				isw3000c01v1OutDelay0TrapEnable
				AlarmEnable,
				isw3000c01v1OutDelay1
				DelayX100Ns,
				isw3000c01v1OutDelay1TrapEnable
				AlarmEnable,
				isw3000c01v1Str1UipDAdd3
				Uint8,
				isw3000c01v1Str1UipDAdd2
				Uint8,
				isw3000c01v1Str1UipDAdd1
				Uint8,
				isw3000c01v1Str1UipDAdd0
				Uint8,
				isw3000c01v1Str1MipDAdd3
				Uint8,
				isw3000c01v1Str1MipDAdd2
				Uint8,
				isw3000c01v1Str1MipDAdd1
				Uint8,
				isw3000c01v1Str1MipDAdd0
				Uint8,
				isw3000c01v1Str1DPortMsb
				Uint8,
				isw3000c01v1Str1DPortLsb
				Uint8,
				isw3000c01v1Str1FecEna
				Bit0No1Yes,
				isw3000c01v1Str1MulticEna
				IpaTxMode,
				isw3000c01v1VlanRx1Enable
				Bit0No1Yes,
				isw3000c01v1VlanRx1Reg1
				Uint8,
				isw3000c01v1VlanRx1Reg2
				Uint8,
				isw3000c01v1Str2UipDAdd3
				Uint8,
				isw3000c01v1Str2UipDAdd2
				Uint8,
				isw3000c01v1Str2UipDAdd1
				Uint8,
				isw3000c01v1Str2UipDAdd0
				Uint8,
				isw3000c01v1Str2MipDAdd3
				Uint8,
				isw3000c01v1Str2MipDAdd2
				Uint8,
				isw3000c01v1Str2MipDAdd1
				Uint8,
				isw3000c01v1Str2MipDAdd0
				Uint8,
				isw3000c01v1Str2DPortMsb
				Uint8,
				isw3000c01v1Str2DPortLsb
				Uint8,
				isw3000c01v1Str2FecEna
				Bit0No1Yes,
				isw3000c01v1Str2MulticEna
				IpaTxMode,
				isw3000c01v1VlanRx2Enable
				Bit0No1Yes,
				isw3000c01v1VlanRx2Reg1
				Uint8,
				isw3000c01v1VlanRx2Reg2
				Uint8,
				isw3000c01v1TxUniEna
				Bit0No1Yes,
				isw3000c01v1TxMultiEna
				IpaTxMode,
				isw3000c01v1LocalIpAdd3
				Uint8,
				isw3000c01v1LocalIpAdd2
				Uint8,
				isw3000c01v1LocalIpAdd1
				Uint8,
				isw3000c01v1LocalIpAdd0
				Uint8,
				isw3000c01v1LocalIpMask3
				Uint8,
				isw3000c01v1LocalIpMask2
				Uint8,
				isw3000c01v1LocalIpMask1
				Uint8,
				isw3000c01v1LocalIpMask0
				Uint8,
				isw3000c01v1LocalIpGway3
				Uint8,
				isw3000c01v1LocalIpGway2
				Uint8,
				isw3000c01v1LocalIpGway1
				Uint8,
				isw3000c01v1LocalIpGway0
				Uint8,
				isw3000c01v1TxUipAdd3
				Uint8,
				isw3000c01v1TxUipAdd2
				Uint8,
				isw3000c01v1TxUipAdd1
				Uint8,
				isw3000c01v1TxUipAdd0
				Uint8,
				isw3000c01v1TxMipAdd3
				Uint8,
				isw3000c01v1TxMipAdd2
				Uint8,
				isw3000c01v1TxMipAdd1
				Uint8,
				isw3000c01v1TxMipAdd0
				Uint8,
				isw3000c01v1TxSPortMsb
				Uint8,
				isw3000c01v1TxSPortLsb
				Uint8,
				isw3000c01v1TxDPortMsb
				Uint8,
				isw3000c01v1TxDPortLsb
				Uint8,
				isw3000c01v1VlanTxEnable
				Bit0No1Yes,
				isw3000c01v1VlanTxPriority
				Uint3,
				isw3000c01v1VlanTxReg1
				Uint8,
				isw3000c01v1VlanTxReg2
				Uint8,
				isw3000c01v1TxLParam
				Uint5,
				isw3000c01v1TxFecMode
				FecMode,
				isw3000c01v1TxDParam
				Uint5,
				isw3000c01v1TxTspkInIppk
				Uint3,
				isw3000c01v1TxRowDelay
				Uint5,
				isw3000c01v1TxColDelay
				Uint8,
				isw3000c01v1LowCost
				Bit0No1Yes,
				isw3000c01v1HighReliabilty
				Bit0No1Yes,
				isw3000c01v1HighThroughput
				Bit0No1Yes,
				isw3000c01v1LowDelay
				Bit0No1Yes,
				isw3000c01v1Precedence
				IpaPrecedence,
				isw3000c01v1Ttl
				Uint8,
				isw3000c01v1Str1IgmFAdd3
				Uint8,
				isw3000c01v1Str1IgmFAdd2
				Uint8,
				isw3000c01v1Str1IgmFAdd1
				Uint8,
				isw3000c01v1Str1IgmFAdd0
				Uint8,
				isw3000c01v1Str2IgmFAdd3
				Uint8,
				isw3000c01v1Str2IgmFAdd2
				Uint8,
				isw3000c01v1Str2IgmFAdd1
				Uint8,
				isw3000c01v1Str2IgmFAdd0
				Uint8,
				isw3000c01v1DvbT2Lock1
				DvbT2Locked,
				isw3000c01v1DvbT2Lock1TrapEnable
				AlarmEnable,
				isw3000c01v1DvbT2Lock2
				DvbT2Locked,
				isw3000c01v1DvbT2Lock2TrapEnable
				AlarmEnable,
				isw3000c01v1Ts1DelayExt
				DelayX02Ms,
				isw3000c01v1Ts2DelayExt
				DelayX02Ms,
				isw3000c01v1DelayT20S
				DelayX1S,
				isw3000c01v1DelayT20Ms
				DelayX100Ns,
				isw3000c01v1DelayT21S
				DelayX1S,
				isw3000c01v1DelayT21Ms
				DelayX100Ns,
				isw3000c01v1Bitrate1
				Bitrate,
				isw3000c01v1Bitrate2
				Bitrate,
				isw3000c01v11ppsFail
				BitFail,
				isw3000c01v11ppsFailTrapEnable
				AlarmEnable,
				isw3000c01v110mhzFail
				BitFail,
				isw3000c01v110mhzFailTrapEnable
				AlarmEnable,
				isw3000c01v1OutputFail
				BitFail,
				isw3000c01v1OutputFailTrapEnable
				AlarmEnable,
				isw3000c01v1Ts1DelWar
				BitFail,
				isw3000c01v1Ts1DelWarTrapEnable
				AlarmEnable,
				isw3000c01v1Ts2DelWar
				BitFail,
				isw3000c01v1Ts2DelWarTrapEnable
				AlarmEnable,
				isw3000c01v1ExtFail1
				BitFail,
				isw3000c01v1ExtFail1TrapEnable
				AlarmEnable,
				isw3000c01v1ExtFail2
				BitFail,
				isw3000c01v1ExtFail2TrapEnable
				AlarmEnable,
				isw3000c01v1GlobalSeam
				Bit0Sea1Nse,
				isw3000c01v1GlobalSeamTrapEnable
				AlarmEnable,
				isw3000c01v1SyncLossErr1
				BitFail,
				isw3000c01v1SyncLossErr1TrapEnable
				AlarmEnable,
				isw3000c01v1SyncByteErr1
				BitFail,
				isw3000c01v1SyncByteErr1TrapEnable
				AlarmEnable,
				isw3000c01v1PatError1
				BitFail,
				isw3000c01v1PatError1TrapEnable
				AlarmEnable,
				isw3000c01v1CcError1
				BitFail,
				isw3000c01v1CcError1TrapEnable
				AlarmEnable,
				isw3000c01v1PmtError1
				BitFail,
				isw3000c01v1PmtError1TrapEnable
				AlarmEnable,
				isw3000c01v1PidError1
				BitFail,
				isw3000c01v1PidError1TrapEnable
				AlarmEnable,
				isw3000c01v1MipError1
				BitFail,
				isw3000c01v1MipError1TrapEnable
				AlarmEnable,
				isw3000c01v1GlobalError1
				BitFail,
				isw3000c01v1GlobalError1TrapEnable
				AlarmEnable,
				isw3000c01v1SyncLossErr2
				BitFail,
				isw3000c01v1SyncLossErr2TrapEnable
				AlarmEnable,
				isw3000c01v1SyncByteErr2
				BitFail,
				isw3000c01v1SyncByteErr2TrapEnable
				AlarmEnable,
				isw3000c01v1PatError2
				BitFail,
				isw3000c01v1PatError2TrapEnable
				AlarmEnable,
				isw3000c01v1CcError2
				BitFail,
				isw3000c01v1CcError2TrapEnable
				AlarmEnable,
				isw3000c01v1PmtError2
				BitFail,
				isw3000c01v1PmtError2TrapEnable
				AlarmEnable,
				isw3000c01v1PidError2
				BitFail,
				isw3000c01v1PidError2TrapEnable
				AlarmEnable,
				isw3000c01v1MipError2
				BitFail,
				isw3000c01v1MipError2TrapEnable
				AlarmEnable,
				isw3000c01v1GlobalError2
				BitFail,
				isw3000c01v1GlobalError2TrapEnable
				AlarmEnable,
				isw3000c01v1IpRxAddress3
				Uint8,
				isw3000c01v1IpRxAddress2
				Uint8,
				isw3000c01v1IpRxAddress1
				Uint8,
				isw3000c01v1IpRxAddress0
				Uint8,
				isw3000c01v1IpRxPort
				Uint16,
				isw3000c01v1LParam
				Uint5,
				isw3000c01v1FecMode
				FecMode,
				isw3000c01v1PacketSize
				Bit02041188,
				isw3000c01v1DParam
				Uint5,
				isw3000c01v1TsPckInIpPck
				Uint3,
				isw3000c01v1PacketRate
				PacketRate,
				isw3000c01v1TimeSinceReset
				TimeS4,
				isw3000c01v1LostIpPck
				Uint16,
				isw3000c01v1RecoveredIpPck
				Uint16,
				isw3000c01v1OutOrdIpPck
				Uint16,
				isw3000c01v1FecRate
				PacketRate,
				isw3000c01v1Link
				IpaEtherStat,
				isw3000c01v1System
				IpaEtherSys,
				isw3000c01v1DestAvailable
				Bit0No1Yes,
				isw3000c01v1Ts1BufOvf
				BitFail,
				isw3000c01v1Ts2BufOvf
				BitFail,
				isw3000c01v1Ts1BufUnd
				BitFail,
				isw3000c01v1Ts2BufUnd
				BitFail,
				isw3000c01v1BufferStatus
				Rate1,
				isw3000c01v1PingStatus
				IpaPingStat,
				isw3000c01v1SerialNo
				SerialNo,
				isw3000c01v1SpeedForce
				Bit0Ann1For,
				isw3000c01v1BadCrcPck
				Uint16,
				isw3000c01v1MaxBitrateNull
				Bitrate,
				isw3000c01v1MinBitrateNull
				Bitrate,
				isw3000c01v1PckNullMax
				PckNullRate1,
				isw3000c01v1PckNullMin
				PckNullRate1,
				isw3000c01v1BitrateNull1
				Bitrate,
				isw3000c01v1BitrateNull2
				Bitrate,
				isw3000c01v1Ts1PckNull
				PckNullRate1,
				isw3000c01v1Ts2PckNull
				PckNullRate1,
				isw3000c01v1BitrateErrorEn
				Bit0No1Yes,
				isw3000c01v1NullPckErrEn
				Bit0No1Yes,
				isw3000c01v1Ts1TraffFail
				BitFail,
				isw3000c01v1Ts1TraffFailTrapEnable
				AlarmEnable,
				isw3000c01v1Ts1NullPFail
				BitFail,
				isw3000c01v1Ts1NullPFailTrapEnable
				AlarmEnable,
				isw3000c01v1Ts2TraffFail
				BitFail,
				isw3000c01v1Ts2TraffFailTrapEnable
				AlarmEnable,
				isw3000c01v1Ts2NullPFail
				BitFail,
				isw3000c01v1Ts2NullPFailTrapEnable
				AlarmEnable,
				isw3000c01v1PidSyncMode
				DvbT2SyncMode,
				isw3000c01v1PidSync
				Uint13,
				isw3000c01v1GlobalError1G
				BitFail,
				isw3000c01v1GlobalError2G
				BitFail,
				isw3000c01v1LeapSecRd0
				Uint8,
				isw3000c01v1LeapSecRd1
				Uint8,
				isw3000c01v1MaxTimeOut
				TimeX1Ms1,
				isw3000c01v1OutDelayT2
				DelayPacket2,
				isw3000c01v1OutDelayT2TrapEnable
				AlarmEnable,
				isw3000c01v1PatErrorTime
				TimeX1Ms1,
				isw3000c01v1PmtErrorTime
				TimeX1Ms1,
				isw3000c01v1MaxDelayTxIp
				TimeX10Ms,
				isw3000c01v1InpFailMode
				Bit0Yes1No
			 }

		-- 1.3.6.1.4.1.10106.3.101291.1.1.1
		isw3000c01v1Index OBJECT-TYPE
			SYNTAX ModuleIndex
			MAX-ACCESS read-only
			STATUS current
			DESCRIPTION
				"Index of ISW3000C01V1 Table"
		::= { isw3000c01v1Entry 1 }

		-- 1.3.6.1.4.1.10106.3.101291.1.1.3
		isw3000c01v1Mode OBJECT-TYPE
			SYNTAX ChgOverMode2
			MAX-ACCESS read-write
			STATUS current
			DESCRIPTION
				"Allows selecting the switching mode"
		::= { isw3000c01v1Entry 3 }

		-- 1.3.6.1.4.1.10106.3.101291.1.1.4
		isw3000c01v1ModeTrapEnable OBJECT-TYPE
			SYNTAX AlarmEnable
			MAX-ACCESS read-write
			STATUS current
			DESCRIPTION
				"Allows selecting the switching mode Trap Enable"
		::= { isw3000c01v1Entry 4 }

		-- 1.3.6.1.4.1.10106.3.101291.1.1.5
		isw3000c01v1DvbTMode OBJECT-TYPE
			SYNTAX DvbTModeIsw
			MAX-ACCESS read-write
			STATUS current
			DESCRIPTION
				"Selects DVB mode."
		::= { isw3000c01v1Entry 5 }

		-- 1.3.6.1.4.1.10106.3.101291.1.1.6
		isw3000c01v1DvbTModeTrapEnable OBJECT-TYPE
			SYNTAX AlarmEnable
			MAX-ACCESS read-write
			STATUS current
			DESCRIPTION
				"Selects DVB mode. Trap Enable"
		::= { isw3000c01v1Entry 6 }

		-- 1.3.6.1.4.1.10106.3.101291.1.1.7
		isw3000c01v1NarrowPllBw OBJECT-TYPE
			SYNTAX Bit0No1Yes
			MAX-ACCESS read-write
			STATUS current
			DESCRIPTION
				"Allows selecting a narrow PLL bandwidth in the clock packet PLL in Generic DVB modeto achieve a very stable bitrate"
		::= { isw3000c01v1Entry 7 }

		-- 1.3.6.1.4.1.10106.3.101291.1.1.9
		isw3000c01v1Buzzer OBJECT-TYPE
			SYNTAX BitMask
			MAX-ACCESS read-write
			STATUS current
			DESCRIPTION
				"Allows buzzer operation"
		::= { isw3000c01v1Entry 9 }

		-- 1.3.6.1.4.1.10106.3.101291.1.1.11
		isw3000c01v1NullPckRtp OBJECT-TYPE
			SYNTAX Bit0No1Yes
			MAX-ACCESS read-write
			STATUS current
			DESCRIPTION
				"Selects if NULL packets are inserted if there are unrecovered packets when using RTP protocol"
		::= { isw3000c01v1Entry 11 }

		-- 1.3.6.1.4.1.10106.3.101291.1.1.13
		isw3000c01v1EnSeamNondvbt OBJECT-TYPE
			SYNTAX Bit0No1Yes
			MAX-ACCESS read-write
			STATUS current
			DESCRIPTION
				"Allows enabling seamless mode with in Generic DVB mode"
		::= { isw3000c01v1Entry 13 }

		-- 1.3.6.1.4.1.10106.3.101291.1.1.15
		isw3000c01v1Input OBJECT-TYPE
			SYNTAX ChgOverIn2T
			MAX-ACCESS read-write
			STATUS current
			DESCRIPTION
				"Selected TS"
		::= { isw3000c01v1Entry 15 }

		-- 1.3.6.1.4.1.10106.3.101291.1.1.16
		isw3000c01v1InputTrapEnable OBJECT-TYPE
			SYNTAX AlarmEnable
			MAX-ACCESS read-write
			STATUS current
			DESCRIPTION
				"Selected TS Trap Enable"
		::= { isw3000c01v1Entry 16 }

		-- 1.3.6.1.4.1.10106.3.101291.1.1.17
		isw3000c01v1InputStChange OBJECT-TYPE
			SYNTAX Bit0No1Yes
			MAX-ACCESS read-write
			STATUS current
			DESCRIPTION
				"Signals a change in fail status"
		::= { isw3000c01v1Entry 17 }

		-- 1.3.6.1.4.1.10106.3.101291.1.1.19
		isw3000c01v1InputChange OBJECT-TYPE
			SYNTAX Bit0No1Yes
			MAX-ACCESS read-write
			STATUS current
			DESCRIPTION
				"Signals a change in selected input"
		::= { isw3000c01v1Entry 19 }

		-- 1.3.6.1.4.1.10106.3.101291.1.1.21
		isw3000c01v1OutDelay OBJECT-TYPE
			SYNTAX DelayX100Ns
			MAX-ACCESS read-write
			STATUS current
			DESCRIPTION
				"Output delay refered to 1PPS reference in DVB-T mode"
		::= { isw3000c01v1Entry 21 }

		-- 1.3.6.1.4.1.10106.3.101291.1.1.22
		isw3000c01v1OutDelayTrapEnable OBJECT-TYPE
			SYNTAX AlarmEnable
			MAX-ACCESS read-write
			STATUS current
			DESCRIPTION
				"Output delay refered to 1PPS reference in DVB-T mode Trap Enable"
		::= { isw3000c01v1Entry 22 }

		-- 1.3.6.1.4.1.10106.3.101291.1.1.23
		isw3000c01v1AsiMainPrior OBJECT-TYPE
			SYNTAX Uint1
			MAX-ACCESS read-write
			STATUS current
			DESCRIPTION
				"Allows selecting the ASI main input priority"
		::= { isw3000c01v1Entry 23 }

		-- 1.3.6.1.4.1.10106.3.101291.1.1.24
		isw3000c01v1AsiMainPriorTrapEnable OBJECT-TYPE
			SYNTAX AlarmEnable
			MAX-ACCESS read-write
			STATUS current
			DESCRIPTION
				"Allows selecting the ASI main input priority Trap Enable"
		::= { isw3000c01v1Entry 24 }

		-- 1.3.6.1.4.1.10106.3.101291.1.1.25
		isw3000c01v1AsiResPrior OBJECT-TYPE
			SYNTAX Uint1
			MAX-ACCESS read-write
			STATUS current
			DESCRIPTION
				"Allows selecting the ASI reserve input priority"
		::= { isw3000c01v1Entry 25 }

		-- 1.3.6.1.4.1.10106.3.101291.1.1.26
		isw3000c01v1AsiResPriorTrapEnable OBJECT-TYPE
			SYNTAX AlarmEnable
			MAX-ACCESS read-write
			STATUS current
			DESCRIPTION
				"Allows selecting the ASI reserve input priority Trap Enable"
		::= { isw3000c01v1Entry 26 }

		-- 1.3.6.1.4.1.10106.3.101291.1.1.27
		isw3000c01v1StatReset OBJECT-TYPE
			SYNTAX Bit0No1Yes
			MAX-ACCESS read-write
			STATUS current
			DESCRIPTION
				"Allows reseting the statistics measurements"
		::= { isw3000c01v1Entry 27 }

		-- 1.3.6.1.4.1.10106.3.101291.1.1.29
		isw3000c01v1StatSel OBJECT-TYPE
			SYNTAX Bit0Ipm1Ipr
			MAX-ACCESS read-write
			STATUS current
			DESCRIPTION
				"Allows selecting the channel to be displayed"
		::= { isw3000c01v1Entry 29 }

		-- 1.3.6.1.4.1.10106.3.101291.1.1.31
		isw3000c01v1StatMode OBJECT-TYPE
			SYNTAX Bit01s1Total
			MAX-ACCESS read-write
			STATUS current
			DESCRIPTION
				"Allows selecting the statistics mode"
		::= { isw3000c01v1Entry 31 }

		-- 1.3.6.1.4.1.10106.3.101291.1.1.33
		isw3000c01v1IgmpVersion OBJECT-TYPE
			SYNTAX Bit0V21V3
			MAX-ACCESS read-write
			STATUS current
			DESCRIPTION
				"Allows selecting the IGMP version"
		::= { isw3000c01v1Entry 33 }

		-- 1.3.6.1.4.1.10106.3.101291.1.1.35
		isw3000c01v1EthMode OBJECT-TYPE
			SYNTAX EthMode
			MAX-ACCESS read-write
			STATUS current
			DESCRIPTION
				"Allows selecting the Ethernet operating mode"
		::= { isw3000c01v1Entry 35 }

		-- 1.3.6.1.4.1.10106.3.101291.1.1.37
		isw3000c01v1PingEnable OBJECT-TYPE
			SYNTAX Bit0No1Yes
			MAX-ACCESS read-write
			STATUS current
			DESCRIPTION
				"Allows making a periodic ping to the unicast address"
		::= { isw3000c01v1Entry 37 }

		-- 1.3.6.1.4.1.10106.3.101291.1.1.39
		isw3000c01v1PacketDelay OBJECT-TYPE
			SYNTAX DelayPacket2
			MAX-ACCESS read-write
			STATUS current
			DESCRIPTION
				"Output delay in TS packets in Generic DVB mode"
		::= { isw3000c01v1Entry 39 }

		-- 1.3.6.1.4.1.10106.3.101291.1.1.40
		isw3000c01v1PacketDelayTrapEnable OBJECT-TYPE
			SYNTAX AlarmEnable
			MAX-ACCESS read-write
			STATUS current
			DESCRIPTION
				"Output delay in TS packets in Generic DVB mode Trap Enable"
		::= { isw3000c01v1Entry 40 }

		-- 1.3.6.1.4.1.10106.3.101291.1.1.41
		isw3000c01v1IpLinkFailEn OBJECT-TYPE
			SYNTAX Bit0No1Yes
			MAX-ACCESS read-write
			STATUS current
			DESCRIPTION
				"IP link lose signals fail in F_OUT GPO"
		::= { isw3000c01v1Entry 41 }

		-- 1.3.6.1.4.1.10106.3.101291.1.1.43
		isw3000c01v1IpDestFailEn OBJECT-TYPE
			SYNTAX Bit0No1Yes
			MAX-ACCESS read-write
			STATUS current
			DESCRIPTION
				"IP destination absence signals fail in F_OUT GPO"
		::= { isw3000c01v1Entry 43 }

		-- 1.3.6.1.4.1.10106.3.101291.1.1.45
		isw3000c01v1TsSyncLossEn OBJECT-TYPE
			SYNTAX Bit0No1Yes
			MAX-ACCESS read-write
			STATUS current
			DESCRIPTION
				"Enables loss of synchronization detection (Fist priority  parameter 1.1)"
		::= { isw3000c01v1Entry 45 }

		-- 1.3.6.1.4.1.10106.3.101291.1.1.47
		isw3000c01v1SyncByErrorEn OBJECT-TYPE
			SYNTAX Bit0No1Yes
			MAX-ACCESS read-write
			STATUS current
			DESCRIPTION
				"Enables sync byte error detection (Fist priority  parameter 1.2)"
		::= { isw3000c01v1Entry 47 }

		-- 1.3.6.1.4.1.10106.3.101291.1.1.49
		isw3000c01v1PatErrorEn OBJECT-TYPE
			SYNTAX Bit0No1Yes
			MAX-ACCESS read-write
			STATUS current
			DESCRIPTION
				"Enables PAT error detection (Fist priority  parameter 1.3)"
		::= { isw3000c01v1Entry 49 }

		-- 1.3.6.1.4.1.10106.3.101291.1.1.51
		isw3000c01v1CcErrorEn OBJECT-TYPE
			SYNTAX Bit0No1Yes
			MAX-ACCESS read-write
			STATUS current
			DESCRIPTION
				"Enables continuity counter error detection (Fist priority  parameter 1.4)"
		::= { isw3000c01v1Entry 51 }

		-- 1.3.6.1.4.1.10106.3.101291.1.1.53
		isw3000c01v1PmtErrorEn OBJECT-TYPE
			SYNTAX Bit0No1Yes
			MAX-ACCESS read-write
			STATUS current
			DESCRIPTION
				"Enables PMT error detection (Fist priority  parameter 1.5)"
		::= { isw3000c01v1Entry 53 }

		-- 1.3.6.1.4.1.10106.3.101291.1.1.55
		isw3000c01v1PidErrorEn OBJECT-TYPE
			SYNTAX Bit0No1Yes
			MAX-ACCESS read-write
			STATUS current
			DESCRIPTION
				"Enables PID error detection (Fist priority  parameter 1.6)"
		::= { isw3000c01v1Entry 55 }

		-- 1.3.6.1.4.1.10106.3.101291.1.1.57
		isw3000c01v1PidErrorTime OBJECT-TYPE
			SYNTAX TimeX1Ms1
			MAX-ACCESS read-write
			STATUS current
			DESCRIPTION
				"PID error time out"
		::= { isw3000c01v1Entry 57 }

		-- 1.3.6.1.4.1.10106.3.101291.1.1.59
		isw3000c01v1Ch1Selection OBJECT-TYPE
			SYNTAX IswChSelection
			MAX-ACCESS read-write
			STATUS current
			DESCRIPTION
				"Channel 1 input selection"
		::= { isw3000c01v1Entry 59 }

		-- 1.3.6.1.4.1.10106.3.101291.1.1.60
		isw3000c01v1Ch1SelectionTrapEnable OBJECT-TYPE
			SYNTAX AlarmEnable
			MAX-ACCESS read-write
			STATUS current
			DESCRIPTION
				"Channel 1 input selection Trap Enable"
		::= { isw3000c01v1Entry 60 }

		-- 1.3.6.1.4.1.10106.3.101291.1.1.61
		isw3000c01v1Ch2Selection OBJECT-TYPE
			SYNTAX IswChSelection
			MAX-ACCESS read-write
			STATUS current
			DESCRIPTION
				"Channel 2 input selection"
		::= { isw3000c01v1Entry 61 }

		-- 1.3.6.1.4.1.10106.3.101291.1.1.62
		isw3000c01v1Ch2SelectionTrapEnable OBJECT-TYPE
			SYNTAX AlarmEnable
			MAX-ACCESS read-write
			STATUS current
			DESCRIPTION
				"Channel 2 input selection Trap Enable"
		::= { isw3000c01v1Entry 62 }

		-- 1.3.6.1.4.1.10106.3.101291.1.1.63
		isw3000c01v1OutDelay0 OBJECT-TYPE
			SYNTAX DelayX1S127
			MAX-ACCESS read-write
			STATUS current
			DESCRIPTION
				"Output time in advance refered to 1PPS or absolute time reference in DVB-T2 mode.  Seconds."
		::= { isw3000c01v1Entry 63 }

		-- 1.3.6.1.4.1.10106.3.101291.1.1.64
		isw3000c01v1OutDelay0TrapEnable OBJECT-TYPE
			SYNTAX AlarmEnable
			MAX-ACCESS read-write
			STATUS current
			DESCRIPTION
				"Output time in advance refered to 1PPS or absolute time reference in DVB-T2 mode.  Seconds. Trap Enable"
		::= { isw3000c01v1Entry 64 }

		-- 1.3.6.1.4.1.10106.3.101291.1.1.65
		isw3000c01v1OutDelay1 OBJECT-TYPE
			SYNTAX DelayX100Ns
			MAX-ACCESS read-write
			STATUS current
			DESCRIPTION
				"Output time in advance refered to 1PPS or absolute time reference in DVB-T2 mode.  Miliseconds."
		::= { isw3000c01v1Entry 65 }

		-- 1.3.6.1.4.1.10106.3.101291.1.1.66
		isw3000c01v1OutDelay1TrapEnable OBJECT-TYPE
			SYNTAX AlarmEnable
			MAX-ACCESS read-write
			STATUS current
			DESCRIPTION
				"Output time in advance refered to 1PPS or absolute time reference in DVB-T2 mode.  Miliseconds. Trap Enable"
		::= { isw3000c01v1Entry 66 }

		-- 1.3.6.1.4.1.10106.3.101291.1.1.67
		isw3000c01v1Str1UipDAdd3 OBJECT-TYPE
			SYNTAX Uint8
			MAX-ACCESS read-write
			STATUS current
			DESCRIPTION
				"Unicast IP address (3)"
		::= { isw3000c01v1Entry 67 }

		-- 1.3.6.1.4.1.10106.3.101291.1.1.69
		isw3000c01v1Str1UipDAdd2 OBJECT-TYPE
			SYNTAX Uint8
			MAX-ACCESS read-write
			STATUS current
			DESCRIPTION
				"Unicast IP address (2)"
		::= { isw3000c01v1Entry 69 }

		-- 1.3.6.1.4.1.10106.3.101291.1.1.71
		isw3000c01v1Str1UipDAdd1 OBJECT-TYPE
			SYNTAX Uint8
			MAX-ACCESS read-write
			STATUS current
			DESCRIPTION
				"Unicast IP address (1)"
		::= { isw3000c01v1Entry 71 }

		-- 1.3.6.1.4.1.10106.3.101291.1.1.73
		isw3000c01v1Str1UipDAdd0 OBJECT-TYPE
			SYNTAX Uint8
			MAX-ACCESS read-write
			STATUS current
			DESCRIPTION
				"Unicast IP address (0)"
		::= { isw3000c01v1Entry 73 }

		-- 1.3.6.1.4.1.10106.3.101291.1.1.75
		isw3000c01v1Str1MipDAdd3 OBJECT-TYPE
			SYNTAX Uint8
			MAX-ACCESS read-write
			STATUS current
			DESCRIPTION
				"Multicast IP address (3)"
		::= { isw3000c01v1Entry 75 }

		-- 1.3.6.1.4.1.10106.3.101291.1.1.77
		isw3000c01v1Str1MipDAdd2 OBJECT-TYPE
			SYNTAX Uint8
			MAX-ACCESS read-write
			STATUS current
			DESCRIPTION
				"Multicast IP address (2)"
		::= { isw3000c01v1Entry 77 }

		-- 1.3.6.1.4.1.10106.3.101291.1.1.79
		isw3000c01v1Str1MipDAdd1 OBJECT-TYPE
			SYNTAX Uint8
			MAX-ACCESS read-write
			STATUS current
			DESCRIPTION
				"Multicast IP address (1)"
		::= { isw3000c01v1Entry 79 }

		-- 1.3.6.1.4.1.10106.3.101291.1.1.81
		isw3000c01v1Str1MipDAdd0 OBJECT-TYPE
			SYNTAX Uint8
			MAX-ACCESS read-write
			STATUS current
			DESCRIPTION
				"Multicast IP address (0)"
		::= { isw3000c01v1Entry 81 }

		-- 1.3.6.1.4.1.10106.3.101291.1.1.83
		isw3000c01v1Str1DPortMsb OBJECT-TYPE
			SYNTAX Uint8
			MAX-ACCESS read-write
			STATUS current
			DESCRIPTION
				"Destination port (msb)"
		::= { isw3000c01v1Entry 83 }

		-- 1.3.6.1.4.1.10106.3.101291.1.1.85
		isw3000c01v1Str1DPortLsb OBJECT-TYPE
			SYNTAX Uint8
			MAX-ACCESS read-write
			STATUS current
			DESCRIPTION
				"Destination port (lsb)"
		::= { isw3000c01v1Entry 85 }

		-- 1.3.6.1.4.1.10106.3.101291.1.1.87
		isw3000c01v1Str1FecEna OBJECT-TYPE
			SYNTAX Bit0No1Yes
			MAX-ACCESS read-write
			STATUS current
			DESCRIPTION
				"Enable FEC"
		::= { isw3000c01v1Entry 87 }

		-- 1.3.6.1.4.1.10106.3.101291.1.1.89
		isw3000c01v1Str1MulticEna OBJECT-TYPE
			SYNTAX IpaTxMode
			MAX-ACCESS read-write
			STATUS current
			DESCRIPTION
				"RX mode"
		::= { isw3000c01v1Entry 89 }

		-- 1.3.6.1.4.1.10106.3.101291.1.1.91
		isw3000c01v1VlanRx1Enable OBJECT-TYPE
			SYNTAX Bit0No1Yes
			MAX-ACCESS read-write
			STATUS current
			DESCRIPTION
				"VLAN Enable"
		::= { isw3000c01v1Entry 91 }

		-- 1.3.6.1.4.1.10106.3.101291.1.1.93
		isw3000c01v1VlanRx1Reg1 OBJECT-TYPE
			SYNTAX Uint8
			MAX-ACCESS read-write
			STATUS current
			DESCRIPTION
				"VLAN_REG_1"
		::= { isw3000c01v1Entry 93 }

		-- 1.3.6.1.4.1.10106.3.101291.1.1.95
		isw3000c01v1VlanRx1Reg2 OBJECT-TYPE
			SYNTAX Uint8
			MAX-ACCESS read-write
			STATUS current
			DESCRIPTION
				"VLAN_REG_2"
		::= { isw3000c01v1Entry 95 }

		-- 1.3.6.1.4.1.10106.3.101291.1.1.97
		isw3000c01v1Str2UipDAdd3 OBJECT-TYPE
			SYNTAX Uint8
			MAX-ACCESS read-write
			STATUS current
			DESCRIPTION
				"Unicast IP address (3)"
		::= { isw3000c01v1Entry 97 }

		-- 1.3.6.1.4.1.10106.3.101291.1.1.99
		isw3000c01v1Str2UipDAdd2 OBJECT-TYPE
			SYNTAX Uint8
			MAX-ACCESS read-write
			STATUS current
			DESCRIPTION
				"Unicast IP address (2)"
		::= { isw3000c01v1Entry 99 }

		-- 1.3.6.1.4.1.10106.3.101291.1.1.101
		isw3000c01v1Str2UipDAdd1 OBJECT-TYPE
			SYNTAX Uint8
			MAX-ACCESS read-write
			STATUS current
			DESCRIPTION
				"Unicast IP address (1)"
		::= { isw3000c01v1Entry 101 }

		-- 1.3.6.1.4.1.10106.3.101291.1.1.103
		isw3000c01v1Str2UipDAdd0 OBJECT-TYPE
			SYNTAX Uint8
			MAX-ACCESS read-write
			STATUS current
			DESCRIPTION
				"Unicast IP address (0)"
		::= { isw3000c01v1Entry 103 }

		-- 1.3.6.1.4.1.10106.3.101291.1.1.105
		isw3000c01v1Str2MipDAdd3 OBJECT-TYPE
			SYNTAX Uint8
			MAX-ACCESS read-write
			STATUS current
			DESCRIPTION
				"Multicast IP address (3)"
		::= { isw3000c01v1Entry 105 }

		-- 1.3.6.1.4.1.10106.3.101291.1.1.107
		isw3000c01v1Str2MipDAdd2 OBJECT-TYPE
			SYNTAX Uint8
			MAX-ACCESS read-write
			STATUS current
			DESCRIPTION
				"Multicast IP address (2)"
		::= { isw3000c01v1Entry 107 }

		-- 1.3.6.1.4.1.10106.3.101291.1.1.109
		isw3000c01v1Str2MipDAdd1 OBJECT-TYPE
			SYNTAX Uint8
			MAX-ACCESS read-write
			STATUS current
			DESCRIPTION
				"Multicast IP address (1)"
		::= { isw3000c01v1Entry 109 }

		-- 1.3.6.1.4.1.10106.3.101291.1.1.111
		isw3000c01v1Str2MipDAdd0 OBJECT-TYPE
			SYNTAX Uint8
			MAX-ACCESS read-write
			STATUS current
			DESCRIPTION
				"Multicast IP address (0)"
		::= { isw3000c01v1Entry 111 }

		-- 1.3.6.1.4.1.10106.3.101291.1.1.113
		isw3000c01v1Str2DPortMsb OBJECT-TYPE
			SYNTAX Uint8
			MAX-ACCESS read-write
			STATUS current
			DESCRIPTION
				"Destination port (msb)"
		::= { isw3000c01v1Entry 113 }

		-- 1.3.6.1.4.1.10106.3.101291.1.1.115
		isw3000c01v1Str2DPortLsb OBJECT-TYPE
			SYNTAX Uint8
			MAX-ACCESS read-write
			STATUS current
			DESCRIPTION
				"Destination port (lsb)"
		::= { isw3000c01v1Entry 115 }

		-- 1.3.6.1.4.1.10106.3.101291.1.1.117
		isw3000c01v1Str2FecEna OBJECT-TYPE
			SYNTAX Bit0No1Yes
			MAX-ACCESS read-write
			STATUS current
			DESCRIPTION
				"Enable FEC"
		::= { isw3000c01v1Entry 117 }

		-- 1.3.6.1.4.1.10106.3.101291.1.1.119
		isw3000c01v1Str2MulticEna OBJECT-TYPE
			SYNTAX IpaTxMode
			MAX-ACCESS read-write
			STATUS current
			DESCRIPTION
				"RX mode"
		::= { isw3000c01v1Entry 119 }

		-- 1.3.6.1.4.1.10106.3.101291.1.1.121
		isw3000c01v1VlanRx2Enable OBJECT-TYPE
			SYNTAX Bit0No1Yes
			MAX-ACCESS read-write
			STATUS current
			DESCRIPTION
				"VLAN Enable"
		::= { isw3000c01v1Entry 121 }

		-- 1.3.6.1.4.1.10106.3.101291.1.1.123
		isw3000c01v1VlanRx2Reg1 OBJECT-TYPE
			SYNTAX Uint8
			MAX-ACCESS read-write
			STATUS current
			DESCRIPTION
				"VLAN_REG_1"
		::= { isw3000c01v1Entry 123 }

		-- 1.3.6.1.4.1.10106.3.101291.1.1.125
		isw3000c01v1VlanRx2Reg2 OBJECT-TYPE
			SYNTAX Uint8
			MAX-ACCESS read-write
			STATUS current
			DESCRIPTION
				"VLAN_REG_2"
		::= { isw3000c01v1Entry 125 }

		-- 1.3.6.1.4.1.10106.3.101291.1.1.127
		isw3000c01v1TxUniEna OBJECT-TYPE
			SYNTAX Bit0No1Yes
			MAX-ACCESS read-write
			STATUS current
			DESCRIPTION
				"Enable TX"
		::= { isw3000c01v1Entry 127 }

		-- 1.3.6.1.4.1.10106.3.101291.1.1.129
		isw3000c01v1TxMultiEna OBJECT-TYPE
			SYNTAX IpaTxMode
			MAX-ACCESS read-write
			STATUS current
			DESCRIPTION
				"TX mode"
		::= { isw3000c01v1Entry 129 }

		-- 1.3.6.1.4.1.10106.3.101291.1.1.131
		isw3000c01v1LocalIpAdd3 OBJECT-TYPE
			SYNTAX Uint8
			MAX-ACCESS read-write
			STATUS current
			DESCRIPTION
				"Unicast IP address (3)"
		::= { isw3000c01v1Entry 131 }

		-- 1.3.6.1.4.1.10106.3.101291.1.1.133
		isw3000c01v1LocalIpAdd2 OBJECT-TYPE
			SYNTAX Uint8
			MAX-ACCESS read-write
			STATUS current
			DESCRIPTION
				"Unicast IP address (2)"
		::= { isw3000c01v1Entry 133 }

		-- 1.3.6.1.4.1.10106.3.101291.1.1.135
		isw3000c01v1LocalIpAdd1 OBJECT-TYPE
			SYNTAX Uint8
			MAX-ACCESS read-write
			STATUS current
			DESCRIPTION
				"Unicast IP address (1)"
		::= { isw3000c01v1Entry 135 }

		-- 1.3.6.1.4.1.10106.3.101291.1.1.137
		isw3000c01v1LocalIpAdd0 OBJECT-TYPE
			SYNTAX Uint8
			MAX-ACCESS read-write
			STATUS current
			DESCRIPTION
				"Unicast IP address (0)"
		::= { isw3000c01v1Entry 137 }

		-- 1.3.6.1.4.1.10106.3.101291.1.1.139
		isw3000c01v1LocalIpMask3 OBJECT-TYPE
			SYNTAX Uint8
			MAX-ACCESS read-write
			STATUS current
			DESCRIPTION
				"IP mask (3)"
		::= { isw3000c01v1Entry 139 }

		-- 1.3.6.1.4.1.10106.3.101291.1.1.141
		isw3000c01v1LocalIpMask2 OBJECT-TYPE
			SYNTAX Uint8
			MAX-ACCESS read-write
			STATUS current
			DESCRIPTION
				"IP mask (2)"
		::= { isw3000c01v1Entry 141 }

		-- 1.3.6.1.4.1.10106.3.101291.1.1.143
		isw3000c01v1LocalIpMask1 OBJECT-TYPE
			SYNTAX Uint8
			MAX-ACCESS read-write
			STATUS current
			DESCRIPTION
				"IP mask (1)"
		::= { isw3000c01v1Entry 143 }

		-- 1.3.6.1.4.1.10106.3.101291.1.1.145
		isw3000c01v1LocalIpMask0 OBJECT-TYPE
			SYNTAX Uint8
			MAX-ACCESS read-write
			STATUS current
			DESCRIPTION
				"IP mask (0)"
		::= { isw3000c01v1Entry 145 }

		-- 1.3.6.1.4.1.10106.3.101291.1.1.147
		isw3000c01v1LocalIpGway3 OBJECT-TYPE
			SYNTAX Uint8
			MAX-ACCESS read-write
			STATUS current
			DESCRIPTION
				"Gateway IP address (3)"
		::= { isw3000c01v1Entry 147 }

		-- 1.3.6.1.4.1.10106.3.101291.1.1.149
		isw3000c01v1LocalIpGway2 OBJECT-TYPE
			SYNTAX Uint8
			MAX-ACCESS read-write
			STATUS current
			DESCRIPTION
				"Gateway IP address (2)"
		::= { isw3000c01v1Entry 149 }

		-- 1.3.6.1.4.1.10106.3.101291.1.1.151
		isw3000c01v1LocalIpGway1 OBJECT-TYPE
			SYNTAX Uint8
			MAX-ACCESS read-write
			STATUS current
			DESCRIPTION
				"Gateway IP address (1)"
		::= { isw3000c01v1Entry 151 }

		-- 1.3.6.1.4.1.10106.3.101291.1.1.153
		isw3000c01v1LocalIpGway0 OBJECT-TYPE
			SYNTAX Uint8
			MAX-ACCESS read-write
			STATUS current
			DESCRIPTION
				"Gateway IP address (0)"
		::= { isw3000c01v1Entry 153 }

		-- 1.3.6.1.4.1.10106.3.101291.1.1.155
		isw3000c01v1TxUipAdd3 OBJECT-TYPE
			SYNTAX Uint8
			MAX-ACCESS read-write
			STATUS current
			DESCRIPTION
				"Destination IP address (3)"
		::= { isw3000c01v1Entry 155 }

		-- 1.3.6.1.4.1.10106.3.101291.1.1.157
		isw3000c01v1TxUipAdd2 OBJECT-TYPE
			SYNTAX Uint8
			MAX-ACCESS read-write
			STATUS current
			DESCRIPTION
				"Destination IP address (2)"
		::= { isw3000c01v1Entry 157 }

		-- 1.3.6.1.4.1.10106.3.101291.1.1.159
		isw3000c01v1TxUipAdd1 OBJECT-TYPE
			SYNTAX Uint8
			MAX-ACCESS read-write
			STATUS current
			DESCRIPTION
				"Destination IP address (1)"
		::= { isw3000c01v1Entry 159 }

		-- 1.3.6.1.4.1.10106.3.101291.1.1.161
		isw3000c01v1TxUipAdd0 OBJECT-TYPE
			SYNTAX Uint8
			MAX-ACCESS read-write
			STATUS current
			DESCRIPTION
				"Destination IP address (0)"
		::= { isw3000c01v1Entry 161 }

		-- 1.3.6.1.4.1.10106.3.101291.1.1.163
		isw3000c01v1TxMipAdd3 OBJECT-TYPE
			SYNTAX Uint8
			MAX-ACCESS read-write
			STATUS current
			DESCRIPTION
				"Multicast dest. IP address (3)"
		::= { isw3000c01v1Entry 163 }

		-- 1.3.6.1.4.1.10106.3.101291.1.1.165
		isw3000c01v1TxMipAdd2 OBJECT-TYPE
			SYNTAX Uint8
			MAX-ACCESS read-write
			STATUS current
			DESCRIPTION
				"Multicast dest. IP address (2)"
		::= { isw3000c01v1Entry 165 }

		-- 1.3.6.1.4.1.10106.3.101291.1.1.167
		isw3000c01v1TxMipAdd1 OBJECT-TYPE
			SYNTAX Uint8
			MAX-ACCESS read-write
			STATUS current
			DESCRIPTION
				"Multicast dest. IP address (1)"
		::= { isw3000c01v1Entry 167 }

		-- 1.3.6.1.4.1.10106.3.101291.1.1.169
		isw3000c01v1TxMipAdd0 OBJECT-TYPE
			SYNTAX Uint8
			MAX-ACCESS read-write
			STATUS current
			DESCRIPTION
				"Multicast dest. IP address (0)"
		::= { isw3000c01v1Entry 169 }

		-- 1.3.6.1.4.1.10106.3.101291.1.1.171
		isw3000c01v1TxSPortMsb OBJECT-TYPE
			SYNTAX Uint8
			MAX-ACCESS read-write
			STATUS current
			DESCRIPTION
				"Source port (msb)"
		::= { isw3000c01v1Entry 171 }

		-- 1.3.6.1.4.1.10106.3.101291.1.1.173
		isw3000c01v1TxSPortLsb OBJECT-TYPE
			SYNTAX Uint8
			MAX-ACCESS read-write
			STATUS current
			DESCRIPTION
				"Source port (lsb)"
		::= { isw3000c01v1Entry 173 }

		-- 1.3.6.1.4.1.10106.3.101291.1.1.175
		isw3000c01v1TxDPortMsb OBJECT-TYPE
			SYNTAX Uint8
			MAX-ACCESS read-write
			STATUS current
			DESCRIPTION
				"Destination port (msb)"
		::= { isw3000c01v1Entry 175 }

		-- 1.3.6.1.4.1.10106.3.101291.1.1.177
		isw3000c01v1TxDPortLsb OBJECT-TYPE
			SYNTAX Uint8
			MAX-ACCESS read-write
			STATUS current
			DESCRIPTION
				"Destination port (lsb)"
		::= { isw3000c01v1Entry 177 }

		-- 1.3.6.1.4.1.10106.3.101291.1.1.179
		isw3000c01v1VlanTxEnable OBJECT-TYPE
			SYNTAX Bit0No1Yes
			MAX-ACCESS read-write
			STATUS current
			DESCRIPTION
				"VLAN Enable"
		::= { isw3000c01v1Entry 179 }

		-- 1.3.6.1.4.1.10106.3.101291.1.1.181
		isw3000c01v1VlanTxPriority OBJECT-TYPE
			SYNTAX Uint3
			MAX-ACCESS read-write
			STATUS current
			DESCRIPTION
				"VLAN Priority"
		::= { isw3000c01v1Entry 181 }

		-- 1.3.6.1.4.1.10106.3.101291.1.1.183
		isw3000c01v1VlanTxReg1 OBJECT-TYPE
			SYNTAX Uint8
			MAX-ACCESS read-write
			STATUS current
			DESCRIPTION
				"VLAN_REG_1"
		::= { isw3000c01v1Entry 183 }

		-- 1.3.6.1.4.1.10106.3.101291.1.1.185
		isw3000c01v1VlanTxReg2 OBJECT-TYPE
			SYNTAX Uint8
			MAX-ACCESS read-write
			STATUS current
			DESCRIPTION
				"VLAN_REG_2"
		::= { isw3000c01v1Entry 185 }

		-- 1.3.6.1.4.1.10106.3.101291.1.1.187
		isw3000c01v1TxLParam OBJECT-TYPE
			SYNTAX Uint5
			MAX-ACCESS read-write
			STATUS current
			DESCRIPTION
				"L parameter (FEC mode columns)"
		::= { isw3000c01v1Entry 187 }

		-- 1.3.6.1.4.1.10106.3.101291.1.1.189
		isw3000c01v1TxFecMode OBJECT-TYPE
			SYNTAX FecMode
			MAX-ACCESS read-write
			STATUS current
			DESCRIPTION
				"Protocol"
		::= { isw3000c01v1Entry 189 }

		-- 1.3.6.1.4.1.10106.3.101291.1.1.191
		isw3000c01v1TxDParam OBJECT-TYPE
			SYNTAX Uint5
			MAX-ACCESS read-write
			STATUS current
			DESCRIPTION
				"D parameter (FEC mode rows)"
		::= { isw3000c01v1Entry 191 }

		-- 1.3.6.1.4.1.10106.3.101291.1.1.193
		isw3000c01v1TxTspkInIppk OBJECT-TYPE
			SYNTAX Uint3
			MAX-ACCESS read-write
			STATUS current
			DESCRIPTION
				"TS packets in each IP packet"
		::= { isw3000c01v1Entry 193 }

		-- 1.3.6.1.4.1.10106.3.101291.1.1.195
		isw3000c01v1TxRowDelay OBJECT-TYPE
			SYNTAX Uint5
			MAX-ACCESS read-write
			STATUS current
			DESCRIPTION
				"FEC row delay"
		::= { isw3000c01v1Entry 195 }

		-- 1.3.6.1.4.1.10106.3.101291.1.1.197
		isw3000c01v1TxColDelay OBJECT-TYPE
			SYNTAX Uint8
			MAX-ACCESS read-write
			STATUS current
			DESCRIPTION
				"FEC column delay"
		::= { isw3000c01v1Entry 197 }

		-- 1.3.6.1.4.1.10106.3.101291.1.1.199
		isw3000c01v1LowCost OBJECT-TYPE
			SYNTAX Bit0No1Yes
			MAX-ACCESS read-write
			STATUS current
			DESCRIPTION
				"TOS.  Low cost"
		::= { isw3000c01v1Entry 199 }

		-- 1.3.6.1.4.1.10106.3.101291.1.1.201
		isw3000c01v1HighReliabilty OBJECT-TYPE
			SYNTAX Bit0No1Yes
			MAX-ACCESS read-write
			STATUS current
			DESCRIPTION
				"TOS. High reliability"
		::= { isw3000c01v1Entry 201 }

		-- 1.3.6.1.4.1.10106.3.101291.1.1.203
		isw3000c01v1HighThroughput OBJECT-TYPE
			SYNTAX Bit0No1Yes
			MAX-ACCESS read-write
			STATUS current
			DESCRIPTION
				"TOS. High Throughput"
		::= { isw3000c01v1Entry 203 }

		-- 1.3.6.1.4.1.10106.3.101291.1.1.205
		isw3000c01v1LowDelay OBJECT-TYPE
			SYNTAX Bit0No1Yes
			MAX-ACCESS read-write
			STATUS current
			DESCRIPTION
				"TOS. Low delay"
		::= { isw3000c01v1Entry 205 }

		-- 1.3.6.1.4.1.10106.3.101291.1.1.207
		isw3000c01v1Precedence OBJECT-TYPE
			SYNTAX IpaPrecedence
			MAX-ACCESS read-write
			STATUS current
			DESCRIPTION
				"TOS. Precedence"
		::= { isw3000c01v1Entry 207 }

		-- 1.3.6.1.4.1.10106.3.101291.1.1.209
		isw3000c01v1Ttl OBJECT-TYPE
			SYNTAX Uint8
			MAX-ACCESS read-write
			STATUS current
			DESCRIPTION
				"Time to live"
		::= { isw3000c01v1Entry 209 }

		-- 1.3.6.1.4.1.10106.3.101291.1.1.211
		isw3000c01v1Str1IgmFAdd3 OBJECT-TYPE
			SYNTAX Uint8
			MAX-ACCESS read-write
			STATUS current
			DESCRIPTION
				"Source IP address (3)"
		::= { isw3000c01v1Entry 211 }

		-- 1.3.6.1.4.1.10106.3.101291.1.1.213
		isw3000c01v1Str1IgmFAdd2 OBJECT-TYPE
			SYNTAX Uint8
			MAX-ACCESS read-write
			STATUS current
			DESCRIPTION
				"Source IP address (2)"
		::= { isw3000c01v1Entry 213 }

		-- 1.3.6.1.4.1.10106.3.101291.1.1.215
		isw3000c01v1Str1IgmFAdd1 OBJECT-TYPE
			SYNTAX Uint8
			MAX-ACCESS read-write
			STATUS current
			DESCRIPTION
				"Source IP address (1)"
		::= { isw3000c01v1Entry 215 }

		-- 1.3.6.1.4.1.10106.3.101291.1.1.217
		isw3000c01v1Str1IgmFAdd0 OBJECT-TYPE
			SYNTAX Uint8
			MAX-ACCESS read-write
			STATUS current
			DESCRIPTION
				"Source IP address (0)"
		::= { isw3000c01v1Entry 217 }

		-- 1.3.6.1.4.1.10106.3.101291.1.1.219
		isw3000c01v1Str2IgmFAdd3 OBJECT-TYPE
			SYNTAX Uint8
			MAX-ACCESS read-write
			STATUS current
			DESCRIPTION
				"Source IP address (3)"
		::= { isw3000c01v1Entry 219 }

		-- 1.3.6.1.4.1.10106.3.101291.1.1.221
		isw3000c01v1Str2IgmFAdd2 OBJECT-TYPE
			SYNTAX Uint8
			MAX-ACCESS read-write
			STATUS current
			DESCRIPTION
				"Source IP address (2)"
		::= { isw3000c01v1Entry 221 }

		-- 1.3.6.1.4.1.10106.3.101291.1.1.223
		isw3000c01v1Str2IgmFAdd1 OBJECT-TYPE
			SYNTAX Uint8
			MAX-ACCESS read-write
			STATUS current
			DESCRIPTION
				"Source IP address (1)"
		::= { isw3000c01v1Entry 223 }

		-- 1.3.6.1.4.1.10106.3.101291.1.1.225
		isw3000c01v1Str2IgmFAdd0 OBJECT-TYPE
			SYNTAX Uint8
			MAX-ACCESS read-write
			STATUS current
			DESCRIPTION
				"Source IP address (0)"
		::= { isw3000c01v1Entry 225 }

		-- 1.3.6.1.4.1.10106.3.101291.1.1.227
		isw3000c01v1DvbT2Lock1 OBJECT-TYPE
			SYNTAX DvbT2Locked
			MAX-ACCESS read-only
			STATUS current
			DESCRIPTION
				"DVB-T2 locked"
		::= { isw3000c01v1Entry 227 }

		-- 1.3.6.1.4.1.10106.3.101291.1.1.228
		isw3000c01v1DvbT2Lock1TrapEnable OBJECT-TYPE
			SYNTAX AlarmEnable
			MAX-ACCESS read-write
			STATUS current
			DESCRIPTION
				"DVB-T2 locked Trap Enable"
		::= { isw3000c01v1Entry 228 }

		-- 1.3.6.1.4.1.10106.3.101291.1.1.229
		isw3000c01v1DvbT2Lock2 OBJECT-TYPE
			SYNTAX DvbT2Locked
			MAX-ACCESS read-only
			STATUS current
			DESCRIPTION
				"DVB-T2 locked"
		::= { isw3000c01v1Entry 229 }

		-- 1.3.6.1.4.1.10106.3.101291.1.1.230
		isw3000c01v1DvbT2Lock2TrapEnable OBJECT-TYPE
			SYNTAX AlarmEnable
			MAX-ACCESS read-write
			STATUS current
			DESCRIPTION
				"DVB-T2 locked Trap Enable"
		::= { isw3000c01v1Entry 230 }

		-- 1.3.6.1.4.1.10106.3.101291.1.1.231
		isw3000c01v1Ts1DelayExt OBJECT-TYPE
			SYNTAX DelayX02Ms
			MAX-ACCESS read-only
			STATUS current
			DESCRIPTION
				"DVB-T mode: input delay refered to 1PPS reference"
		::= { isw3000c01v1Entry 231 }

		-- 1.3.6.1.4.1.10106.3.101291.1.1.233
		isw3000c01v1Ts2DelayExt OBJECT-TYPE
			SYNTAX DelayX02Ms
			MAX-ACCESS read-only
			STATUS current
			DESCRIPTION
				"DVB-T mode: input delay refered to 1PPS reference"
		::= { isw3000c01v1Entry 233 }

		-- 1.3.6.1.4.1.10106.3.101291.1.1.235
		isw3000c01v1DelayT20S OBJECT-TYPE
			SYNTAX DelayX1S
			MAX-ACCESS read-only
			STATUS current
			DESCRIPTION
				"Seconds in advance (DVB-T2 absolute mode only)"
		::= { isw3000c01v1Entry 235 }

		-- 1.3.6.1.4.1.10106.3.101291.1.1.237
		isw3000c01v1DelayT20Ms OBJECT-TYPE
			SYNTAX DelayX100Ns
			MAX-ACCESS read-only
			STATUS current
			DESCRIPTION
				"Time in advance in ns (DVB-T2 mode)"
		::= { isw3000c01v1Entry 237 }

		-- 1.3.6.1.4.1.10106.3.101291.1.1.239
		isw3000c01v1DelayT21S OBJECT-TYPE
			SYNTAX DelayX1S
			MAX-ACCESS read-only
			STATUS current
			DESCRIPTION
				"Seconds in advance (DVB-T2 absolute mode only)"
		::= { isw3000c01v1Entry 239 }

		-- 1.3.6.1.4.1.10106.3.101291.1.1.241
		isw3000c01v1DelayT21Ms OBJECT-TYPE
			SYNTAX DelayX100Ns
			MAX-ACCESS read-only
			STATUS current
			DESCRIPTION
				"Time in advance in ns (DVB-T2 mode)"
		::= { isw3000c01v1Entry 241 }

		-- 1.3.6.1.4.1.10106.3.101291.1.1.243
		isw3000c01v1Bitrate1 OBJECT-TYPE
			SYNTAX Bitrate
			MAX-ACCESS read-only
			STATUS current
			DESCRIPTION
				"Bitrate"
		::= { isw3000c01v1Entry 243 }

		-- 1.3.6.1.4.1.10106.3.101291.1.1.245
		isw3000c01v1Bitrate2 OBJECT-TYPE
			SYNTAX Bitrate
			MAX-ACCESS read-only
			STATUS current
			DESCRIPTION
				"Bitrate"
		::= { isw3000c01v1Entry 245 }

		-- 1.3.6.1.4.1.10106.3.101291.1.1.247
		isw3000c01v11ppsFail OBJECT-TYPE
			SYNTAX BitFail
			MAX-ACCESS read-only
			STATUS current
			DESCRIPTION
				"1PPS reference input status"
		::= { isw3000c01v1Entry 247 }

		-- 1.3.6.1.4.1.10106.3.101291.1.1.248
		isw3000c01v11ppsFailTrapEnable OBJECT-TYPE
			SYNTAX AlarmEnable
			MAX-ACCESS read-write
			STATUS current
			DESCRIPTION
				"1PPS reference input status Trap Enable"
		::= { isw3000c01v1Entry 248 }

		-- 1.3.6.1.4.1.10106.3.101291.1.1.249
		isw3000c01v110mhzFail OBJECT-TYPE
			SYNTAX BitFail
			MAX-ACCESS read-only
			STATUS current
			DESCRIPTION
				"10MHz reference input status"
		::= { isw3000c01v1Entry 249 }

		-- 1.3.6.1.4.1.10106.3.101291.1.1.250
		isw3000c01v110mhzFailTrapEnable OBJECT-TYPE
			SYNTAX AlarmEnable
			MAX-ACCESS read-write
			STATUS current
			DESCRIPTION
				"10MHz reference input status Trap Enable"
		::= { isw3000c01v1Entry 250 }

		-- 1.3.6.1.4.1.10106.3.101291.1.1.251
		isw3000c01v1OutputFail OBJECT-TYPE
			SYNTAX BitFail
			MAX-ACCESS read-only
			STATUS current
			DESCRIPTION
				"The output signal is not valid because all inputs failed"
		::= { isw3000c01v1Entry 251 }

		-- 1.3.6.1.4.1.10106.3.101291.1.1.252
		isw3000c01v1OutputFailTrapEnable OBJECT-TYPE
			SYNTAX AlarmEnable
			MAX-ACCESS read-write
			STATUS current
			DESCRIPTION
				"The output signal is not valid because all inputs failed Trap Enable"
		::= { isw3000c01v1Entry 252 }

		-- 1.3.6.1.4.1.10106.3.101291.1.1.253
		isw3000c01v1Ts1DelWar OBJECT-TYPE
			SYNTAX BitFail
			MAX-ACCESS read-only
			STATUS current
			DESCRIPTION
				"The delay is greater than the programmed output delay"
		::= { isw3000c01v1Entry 253 }

		-- 1.3.6.1.4.1.10106.3.101291.1.1.254
		isw3000c01v1Ts1DelWarTrapEnable OBJECT-TYPE
			SYNTAX AlarmEnable
			MAX-ACCESS read-write
			STATUS current
			DESCRIPTION
				"The delay is greater than the programmed output delay Trap Enable"
		::= { isw3000c01v1Entry 254 }

		-- 1.3.6.1.4.1.10106.3.101291.1.1.255
		isw3000c01v1Ts2DelWar OBJECT-TYPE
			SYNTAX BitFail
			MAX-ACCESS read-only
			STATUS current
			DESCRIPTION
				"The delay is greater than the programmed output delay"
		::= { isw3000c01v1Entry 255 }

		-- 1.3.6.1.4.1.10106.3.101291.1.1.256
		isw3000c01v1Ts2DelWarTrapEnable OBJECT-TYPE
			SYNTAX AlarmEnable
			MAX-ACCESS read-write
			STATUS current
			DESCRIPTION
				"The delay is greater than the programmed output delay Trap Enable"
		::= { isw3000c01v1Entry 256 }

		-- 1.3.6.1.4.1.10106.3.101291.1.1.257
		isw3000c01v1ExtFail1 OBJECT-TYPE
			SYNTAX BitFail
			MAX-ACCESS read-only
			STATUS current
			DESCRIPTION
				"External input fail status"
		::= { isw3000c01v1Entry 257 }

		-- 1.3.6.1.4.1.10106.3.101291.1.1.258
		isw3000c01v1ExtFail1TrapEnable OBJECT-TYPE
			SYNTAX AlarmEnable
			MAX-ACCESS read-write
			STATUS current
			DESCRIPTION
				"External input fail status Trap Enable"
		::= { isw3000c01v1Entry 258 }

		-- 1.3.6.1.4.1.10106.3.101291.1.1.259
		isw3000c01v1ExtFail2 OBJECT-TYPE
			SYNTAX BitFail
			MAX-ACCESS read-only
			STATUS current
			DESCRIPTION
				"External input fail status"
		::= { isw3000c01v1Entry 259 }

		-- 1.3.6.1.4.1.10106.3.101291.1.1.260
		isw3000c01v1ExtFail2TrapEnable OBJECT-TYPE
			SYNTAX AlarmEnable
			MAX-ACCESS read-write
			STATUS current
			DESCRIPTION
				"External input fail status Trap Enable"
		::= { isw3000c01v1Entry 260 }

		-- 1.3.6.1.4.1.10106.3.101291.1.1.261
		isw3000c01v1GlobalSeam OBJECT-TYPE
			SYNTAX Bit0Sea1Nse
			MAX-ACCESS read-only
			STATUS current
			DESCRIPTION
				"Global seamles switching capability"
		::= { isw3000c01v1Entry 261 }

		-- 1.3.6.1.4.1.10106.3.101291.1.1.262
		isw3000c01v1GlobalSeamTrapEnable OBJECT-TYPE
			SYNTAX AlarmEnable
			MAX-ACCESS read-write
			STATUS current
			DESCRIPTION
				"Global seamles switching capability Trap Enable"
		::= { isw3000c01v1Entry 262 }

		-- 1.3.6.1.4.1.10106.3.101291.1.1.263
		isw3000c01v1SyncLossErr1 OBJECT-TYPE
			SYNTAX BitFail
			MAX-ACCESS read-only
			STATUS current
			DESCRIPTION
				"Sync loss fail (Fist priority  parameter 1.1)"
		::= { isw3000c01v1Entry 263 }

		-- 1.3.6.1.4.1.10106.3.101291.1.1.264
		isw3000c01v1SyncLossErr1TrapEnable OBJECT-TYPE
			SYNTAX AlarmEnable
			MAX-ACCESS read-write
			STATUS current
			DESCRIPTION
				"Sync loss fail (Fist priority  parameter 1.1) Trap Enable"
		::= { isw3000c01v1Entry 264 }

		-- 1.3.6.1.4.1.10106.3.101291.1.1.265
		isw3000c01v1SyncByteErr1 OBJECT-TYPE
			SYNTAX BitFail
			MAX-ACCESS read-only
			STATUS current
			DESCRIPTION
				"Sync byte error (Fist priority  parameter 1.2)"
		::= { isw3000c01v1Entry 265 }

		-- 1.3.6.1.4.1.10106.3.101291.1.1.266
		isw3000c01v1SyncByteErr1TrapEnable OBJECT-TYPE
			SYNTAX AlarmEnable
			MAX-ACCESS read-write
			STATUS current
			DESCRIPTION
				"Sync byte error (Fist priority  parameter 1.2) Trap Enable"
		::= { isw3000c01v1Entry 266 }

		-- 1.3.6.1.4.1.10106.3.101291.1.1.267
		isw3000c01v1PatError1 OBJECT-TYPE
			SYNTAX BitFail
			MAX-ACCESS read-only
			STATUS current
			DESCRIPTION
				"PAT error (Fist priority  parameter 1.3)"
		::= { isw3000c01v1Entry 267 }

		-- 1.3.6.1.4.1.10106.3.101291.1.1.268
		isw3000c01v1PatError1TrapEnable OBJECT-TYPE
			SYNTAX AlarmEnable
			MAX-ACCESS read-write
			STATUS current
			DESCRIPTION
				"PAT error (Fist priority  parameter 1.3) Trap Enable"
		::= { isw3000c01v1Entry 268 }

		-- 1.3.6.1.4.1.10106.3.101291.1.1.269
		isw3000c01v1CcError1 OBJECT-TYPE
			SYNTAX BitFail
			MAX-ACCESS read-only
			STATUS current
			DESCRIPTION
				"Continuity counter error (Fist priority  parameter 1.4)"
		::= { isw3000c01v1Entry 269 }

		-- 1.3.6.1.4.1.10106.3.101291.1.1.270
		isw3000c01v1CcError1TrapEnable OBJECT-TYPE
			SYNTAX AlarmEnable
			MAX-ACCESS read-write
			STATUS current
			DESCRIPTION
				"Continuity counter error (Fist priority  parameter 1.4) Trap Enable"
		::= { isw3000c01v1Entry 270 }

		-- 1.3.6.1.4.1.10106.3.101291.1.1.271
		isw3000c01v1PmtError1 OBJECT-TYPE
			SYNTAX BitFail
			MAX-ACCESS read-only
			STATUS current
			DESCRIPTION
				"PMT error (Fist priority  parameter 1.5)"
		::= { isw3000c01v1Entry 271 }

		-- 1.3.6.1.4.1.10106.3.101291.1.1.272
		isw3000c01v1PmtError1TrapEnable OBJECT-TYPE
			SYNTAX AlarmEnable
			MAX-ACCESS read-write
			STATUS current
			DESCRIPTION
				"PMT error (Fist priority  parameter 1.5) Trap Enable"
		::= { isw3000c01v1Entry 272 }

		-- 1.3.6.1.4.1.10106.3.101291.1.1.273
		isw3000c01v1PidError1 OBJECT-TYPE
			SYNTAX BitFail
			MAX-ACCESS read-only
			STATUS current
			DESCRIPTION
				"PID error (Fist priority  parameter 1.6)"
		::= { isw3000c01v1Entry 273 }

		-- 1.3.6.1.4.1.10106.3.101291.1.1.274
		isw3000c01v1PidError1TrapEnable OBJECT-TYPE
			SYNTAX AlarmEnable
			MAX-ACCESS read-write
			STATUS current
			DESCRIPTION
				"PID error (Fist priority  parameter 1.6) Trap Enable"
		::= { isw3000c01v1Entry 274 }

		-- 1.3.6.1.4.1.10106.3.101291.1.1.275
		isw3000c01v1MipError1 OBJECT-TYPE
			SYNTAX BitFail
			MAX-ACCESS read-only
			STATUS current
			DESCRIPTION
				"MIP error. DVB-T compliant"
		::= { isw3000c01v1Entry 275 }

		-- 1.3.6.1.4.1.10106.3.101291.1.1.276
		isw3000c01v1MipError1TrapEnable OBJECT-TYPE
			SYNTAX AlarmEnable
			MAX-ACCESS read-write
			STATUS current
			DESCRIPTION
				"MIP error. DVB-T compliant Trap Enable"
		::= { isw3000c01v1Entry 276 }

		-- 1.3.6.1.4.1.10106.3.101291.1.1.277
		isw3000c01v1GlobalError1 OBJECT-TYPE
			SYNTAX BitFail
			MAX-ACCESS read-only
			STATUS current
			DESCRIPTION
				"Global fail"
		::= { isw3000c01v1Entry 277 }

		-- 1.3.6.1.4.1.10106.3.101291.1.1.278
		isw3000c01v1GlobalError1TrapEnable OBJECT-TYPE
			SYNTAX AlarmEnable
			MAX-ACCESS read-write
			STATUS current
			DESCRIPTION
				"Global fail Trap Enable"
		::= { isw3000c01v1Entry 278 }

		-- 1.3.6.1.4.1.10106.3.101291.1.1.279
		isw3000c01v1SyncLossErr2 OBJECT-TYPE
			SYNTAX BitFail
			MAX-ACCESS read-only
			STATUS current
			DESCRIPTION
				"Sync loss fail (Fist priority  parameter 1.1)"
		::= { isw3000c01v1Entry 279 }

		-- 1.3.6.1.4.1.10106.3.101291.1.1.280
		isw3000c01v1SyncLossErr2TrapEnable OBJECT-TYPE
			SYNTAX AlarmEnable
			MAX-ACCESS read-write
			STATUS current
			DESCRIPTION
				"Sync loss fail (Fist priority  parameter 1.1) Trap Enable"
		::= { isw3000c01v1Entry 280 }

		-- 1.3.6.1.4.1.10106.3.101291.1.1.281
		isw3000c01v1SyncByteErr2 OBJECT-TYPE
			SYNTAX BitFail
			MAX-ACCESS read-only
			STATUS current
			DESCRIPTION
				"Sync byte error (Fist priority  parameter 1.2)"
		::= { isw3000c01v1Entry 281 }

		-- 1.3.6.1.4.1.10106.3.101291.1.1.282
		isw3000c01v1SyncByteErr2TrapEnable OBJECT-TYPE
			SYNTAX AlarmEnable
			MAX-ACCESS read-write
			STATUS current
			DESCRIPTION
				"Sync byte error (Fist priority  parameter 1.2) Trap Enable"
		::= { isw3000c01v1Entry 282 }

		-- 1.3.6.1.4.1.10106.3.101291.1.1.283
		isw3000c01v1PatError2 OBJECT-TYPE
			SYNTAX BitFail
			MAX-ACCESS read-only
			STATUS current
			DESCRIPTION
				"PAT error (Fist priority  parameter 1.3)"
		::= { isw3000c01v1Entry 283 }

		-- 1.3.6.1.4.1.10106.3.101291.1.1.284
		isw3000c01v1PatError2TrapEnable OBJECT-TYPE
			SYNTAX AlarmEnable
			MAX-ACCESS read-write
			STATUS current
			DESCRIPTION
				"PAT error (Fist priority  parameter 1.3) Trap Enable"
		::= { isw3000c01v1Entry 284 }

		-- 1.3.6.1.4.1.10106.3.101291.1.1.285
		isw3000c01v1CcError2 OBJECT-TYPE
			SYNTAX BitFail
			MAX-ACCESS read-only
			STATUS current
			DESCRIPTION
				"Continuity counter error (Fist priority  parameter 1.4)"
		::= { isw3000c01v1Entry 285 }

		-- 1.3.6.1.4.1.10106.3.101291.1.1.286
		isw3000c01v1CcError2TrapEnable OBJECT-TYPE
			SYNTAX AlarmEnable
			MAX-ACCESS read-write
			STATUS current
			DESCRIPTION
				"Continuity counter error (Fist priority  parameter 1.4) Trap Enable"
		::= { isw3000c01v1Entry 286 }

		-- 1.3.6.1.4.1.10106.3.101291.1.1.287
		isw3000c01v1PmtError2 OBJECT-TYPE
			SYNTAX BitFail
			MAX-ACCESS read-only
			STATUS current
			DESCRIPTION
				"PMT error (Fist priority  parameter 1.5)"
		::= { isw3000c01v1Entry 287 }

		-- 1.3.6.1.4.1.10106.3.101291.1.1.288
		isw3000c01v1PmtError2TrapEnable OBJECT-TYPE
			SYNTAX AlarmEnable
			MAX-ACCESS read-write
			STATUS current
			DESCRIPTION
				"PMT error (Fist priority  parameter 1.5) Trap Enable"
		::= { isw3000c01v1Entry 288 }

		-- 1.3.6.1.4.1.10106.3.101291.1.1.289
		isw3000c01v1PidError2 OBJECT-TYPE
			SYNTAX BitFail
			MAX-ACCESS read-only
			STATUS current
			DESCRIPTION
				"PID error (Fist priority  parameter 1.6)"
		::= { isw3000c01v1Entry 289 }

		-- 1.3.6.1.4.1.10106.3.101291.1.1.290
		isw3000c01v1PidError2TrapEnable OBJECT-TYPE
			SYNTAX AlarmEnable
			MAX-ACCESS read-write
			STATUS current
			DESCRIPTION
				"PID error (Fist priority  parameter 1.6) Trap Enable"
		::= { isw3000c01v1Entry 290 }

		-- 1.3.6.1.4.1.10106.3.101291.1.1.291
		isw3000c01v1MipError2 OBJECT-TYPE
			SYNTAX BitFail
			MAX-ACCESS read-only
			STATUS current
			DESCRIPTION
				"MIP error. DVB-T compliant"
		::= { isw3000c01v1Entry 291 }

		-- 1.3.6.1.4.1.10106.3.101291.1.1.292
		isw3000c01v1MipError2TrapEnable OBJECT-TYPE
			SYNTAX AlarmEnable
			MAX-ACCESS read-write
			STATUS current
			DESCRIPTION
				"MIP error. DVB-T compliant Trap Enable"
		::= { isw3000c01v1Entry 292 }

		-- 1.3.6.1.4.1.10106.3.101291.1.1.293
		isw3000c01v1GlobalError2 OBJECT-TYPE
			SYNTAX BitFail
			MAX-ACCESS read-only
			STATUS current
			DESCRIPTION
				"Global fail"
		::= { isw3000c01v1Entry 293 }

		-- 1.3.6.1.4.1.10106.3.101291.1.1.294
		isw3000c01v1GlobalError2TrapEnable OBJECT-TYPE
			SYNTAX AlarmEnable
			MAX-ACCESS read-write
			STATUS current
			DESCRIPTION
				"Global fail Trap Enable"
		::= { isw3000c01v1Entry 294 }

		-- 1.3.6.1.4.1.10106.3.101291.1.1.295
		isw3000c01v1IpRxAddress3 OBJECT-TYPE
			SYNTAX Uint8
			MAX-ACCESS read-only
			STATUS current
			DESCRIPTION
				"RX packets source IP address (3)"
		::= { isw3000c01v1Entry 295 }

		-- 1.3.6.1.4.1.10106.3.101291.1.1.297
		isw3000c01v1IpRxAddress2 OBJECT-TYPE
			SYNTAX Uint8
			MAX-ACCESS read-only
			STATUS current
			DESCRIPTION
				"RX packets source IP address (2)"
		::= { isw3000c01v1Entry 297 }

		-- 1.3.6.1.4.1.10106.3.101291.1.1.299
		isw3000c01v1IpRxAddress1 OBJECT-TYPE
			SYNTAX Uint8
			MAX-ACCESS read-only
			STATUS current
			DESCRIPTION
				"RX packets source IP address (1)"
		::= { isw3000c01v1Entry 299 }

		-- 1.3.6.1.4.1.10106.3.101291.1.1.301
		isw3000c01v1IpRxAddress0 OBJECT-TYPE
			SYNTAX Uint8
			MAX-ACCESS read-only
			STATUS current
			DESCRIPTION
				"RX packets source IP address (0)"
		::= { isw3000c01v1Entry 301 }

		-- 1.3.6.1.4.1.10106.3.101291.1.1.303
		isw3000c01v1IpRxPort OBJECT-TYPE
			SYNTAX Uint16
			MAX-ACCESS read-only
			STATUS current
			DESCRIPTION
				"RX packets UDP source port"
		::= { isw3000c01v1Entry 303 }

		-- 1.3.6.1.4.1.10106.3.101291.1.1.305
		isw3000c01v1LParam OBJECT-TYPE
			SYNTAX Uint5
			MAX-ACCESS read-only
			STATUS current
			DESCRIPTION
				"L parameter (FEC mode columns)"
		::= { isw3000c01v1Entry 305 }

		-- 1.3.6.1.4.1.10106.3.101291.1.1.307
		isw3000c01v1FecMode OBJECT-TYPE
			SYNTAX FecMode
			MAX-ACCESS read-only
			STATUS current
			DESCRIPTION
				"Protocol"
		::= { isw3000c01v1Entry 307 }

		-- 1.3.6.1.4.1.10106.3.101291.1.1.309
		isw3000c01v1PacketSize OBJECT-TYPE
			SYNTAX Bit02041188
			MAX-ACCESS read-only
			STATUS current
			DESCRIPTION
				"Bytes in TS packets"
		::= { isw3000c01v1Entry 309 }

		-- 1.3.6.1.4.1.10106.3.101291.1.1.311
		isw3000c01v1DParam OBJECT-TYPE
			SYNTAX Uint5
			MAX-ACCESS read-only
			STATUS current
			DESCRIPTION
				"D parameter (FEC mode rows)"
		::= { isw3000c01v1Entry 311 }

		-- 1.3.6.1.4.1.10106.3.101291.1.1.313
		isw3000c01v1TsPckInIpPck OBJECT-TYPE
			SYNTAX Uint3
			MAX-ACCESS read-only
			STATUS current
			DESCRIPTION
				"TS packets in each IP packet"
		::= { isw3000c01v1Entry 313 }

		-- 1.3.6.1.4.1.10106.3.101291.1.1.315
		isw3000c01v1PacketRate OBJECT-TYPE
			SYNTAX PacketRate
			MAX-ACCESS read-only
			STATUS current
			DESCRIPTION
				"IP packet rate"
		::= { isw3000c01v1Entry 315 }

		-- 1.3.6.1.4.1.10106.3.101291.1.1.317
		isw3000c01v1TimeSinceReset OBJECT-TYPE
			SYNTAX TimeS4
			MAX-ACCESS read-only
			STATUS current
			DESCRIPTION
				"Elapsed time from last reset"
		::= { isw3000c01v1Entry 317 }

		-- 1.3.6.1.4.1.10106.3.101291.1.1.319
		isw3000c01v1LostIpPck OBJECT-TYPE
			SYNTAX Uint16
			MAX-ACCESS read-only
			STATUS current
			DESCRIPTION
				"Lost IP packets"
		::= { isw3000c01v1Entry 319 }

		-- 1.3.6.1.4.1.10106.3.101291.1.1.321
		isw3000c01v1RecoveredIpPck OBJECT-TYPE
			SYNTAX Uint16
			MAX-ACCESS read-only
			STATUS current
			DESCRIPTION
				"Recovered IP packets"
		::= { isw3000c01v1Entry 321 }

		-- 1.3.6.1.4.1.10106.3.101291.1.1.323
		isw3000c01v1OutOrdIpPck OBJECT-TYPE
			SYNTAX Uint16
			MAX-ACCESS read-only
			STATUS current
			DESCRIPTION
				"Out of order IP packets"
		::= { isw3000c01v1Entry 323 }

		-- 1.3.6.1.4.1.10106.3.101291.1.1.325
		isw3000c01v1FecRate OBJECT-TYPE
			SYNTAX PacketRate
			MAX-ACCESS read-only
			STATUS current
			DESCRIPTION
				"FEC packet rate"
		::= { isw3000c01v1Entry 325 }

		-- 1.3.6.1.4.1.10106.3.101291.1.1.327
		isw3000c01v1Link OBJECT-TYPE
			SYNTAX IpaEtherStat
			MAX-ACCESS read-only
			STATUS current
			DESCRIPTION
				"Ethernet conection status"
		::= { isw3000c01v1Entry 327 }

		-- 1.3.6.1.4.1.10106.3.101291.1.1.329
		isw3000c01v1System OBJECT-TYPE
			SYNTAX IpaEtherSys
			MAX-ACCESS read-only
			STATUS current
			DESCRIPTION
				"Ethernet conection system"
		::= { isw3000c01v1Entry 329 }

		-- 1.3.6.1.4.1.10106.3.101291.1.1.331
		isw3000c01v1DestAvailable OBJECT-TYPE
			SYNTAX Bit0No1Yes
			MAX-ACCESS read-only
			STATUS current
			DESCRIPTION
				"Destination IP available"
		::= { isw3000c01v1Entry 331 }

		-- 1.3.6.1.4.1.10106.3.101291.1.1.333
		isw3000c01v1Ts1BufOvf OBJECT-TYPE
			SYNTAX BitFail
			MAX-ACCESS read-only
			STATUS current
			DESCRIPTION
				"Buffer overflow"
		::= { isw3000c01v1Entry 333 }

		-- 1.3.6.1.4.1.10106.3.101291.1.1.335
		isw3000c01v1Ts2BufOvf OBJECT-TYPE
			SYNTAX BitFail
			MAX-ACCESS read-only
			STATUS current
			DESCRIPTION
				"Buffer overflow"
		::= { isw3000c01v1Entry 335 }

		-- 1.3.6.1.4.1.10106.3.101291.1.1.337
		isw3000c01v1Ts1BufUnd OBJECT-TYPE
			SYNTAX BitFail
			MAX-ACCESS read-only
			STATUS current
			DESCRIPTION
				"Buffer underflow"
		::= { isw3000c01v1Entry 337 }

		-- 1.3.6.1.4.1.10106.3.101291.1.1.339
		isw3000c01v1Ts2BufUnd OBJECT-TYPE
			SYNTAX BitFail
			MAX-ACCESS read-only
			STATUS current
			DESCRIPTION
				"Buffer underflow"
		::= { isw3000c01v1Entry 339 }

		-- 1.3.6.1.4.1.10106.3.101291.1.1.341
		isw3000c01v1BufferStatus OBJECT-TYPE
			SYNTAX Rate1
			MAX-ACCESS read-only
			STATUS current
			DESCRIPTION
				"Buffer filling status"
		::= { isw3000c01v1Entry 341 }

		-- 1.3.6.1.4.1.10106.3.101291.1.1.343
		isw3000c01v1PingStatus OBJECT-TYPE
			SYNTAX IpaPingStat
			MAX-ACCESS read-only
			STATUS current
			DESCRIPTION
				"Ping status"
		::= { isw3000c01v1Entry 343 }

		-- 1.3.6.1.4.1.10106.3.101291.1.1.345
		isw3000c01v1SerialNo OBJECT-TYPE
			SYNTAX SerialNo
			MAX-ACCESS read-only
			STATUS current
			DESCRIPTION
				"Serial number"
		::= { isw3000c01v1Entry 345 }

		-- 1.3.6.1.4.1.10106.3.101291.1.1.347
		isw3000c01v1SpeedForce OBJECT-TYPE
			SYNTAX Bit0Ann1For
			MAX-ACCESS read-write
			STATUS current
			DESCRIPTION
				"Allows selecting if the speed/mode is forced or announced for autonegotiation"
		::= { isw3000c01v1Entry 347 }

		-- 1.3.6.1.4.1.10106.3.101291.1.1.349
		isw3000c01v1BadCrcPck OBJECT-TYPE
			SYNTAX Uint16
			MAX-ACCESS read-only
			STATUS current
			DESCRIPTION
				"Bad CRC packets"
		::= { isw3000c01v1Entry 349 }

		-- 1.3.6.1.4.1.10106.3.101291.1.1.351
		isw3000c01v1MaxBitrateNull OBJECT-TYPE
			SYNTAX Bitrate
			MAX-ACCESS read-write
			STATUS current
			DESCRIPTION
				"Upper bitrate limit"
		::= { isw3000c01v1Entry 351 }

		-- 1.3.6.1.4.1.10106.3.101291.1.1.353
		isw3000c01v1MinBitrateNull OBJECT-TYPE
			SYNTAX Bitrate
			MAX-ACCESS read-write
			STATUS current
			DESCRIPTION
				"Lower bitrate limit"
		::= { isw3000c01v1Entry 353 }

		-- 1.3.6.1.4.1.10106.3.101291.1.1.355
		isw3000c01v1PckNullMax OBJECT-TYPE
			SYNTAX PckNullRate1
			MAX-ACCESS read-write
			STATUS current
			DESCRIPTION
				"Upper packet null ratio limit"
		::= { isw3000c01v1Entry 355 }

		-- 1.3.6.1.4.1.10106.3.101291.1.1.357
		isw3000c01v1PckNullMin OBJECT-TYPE
			SYNTAX PckNullRate1
			MAX-ACCESS read-write
			STATUS current
			DESCRIPTION
				"Lower packet null ratio limit"
		::= { isw3000c01v1Entry 357 }

		-- 1.3.6.1.4.1.10106.3.101291.1.1.359
		isw3000c01v1BitrateNull1 OBJECT-TYPE
			SYNTAX Bitrate
			MAX-ACCESS read-only
			STATUS current
			DESCRIPTION
				"Bitrate null packets"
		::= { isw3000c01v1Entry 359 }

		-- 1.3.6.1.4.1.10106.3.101291.1.1.361
		isw3000c01v1BitrateNull2 OBJECT-TYPE
			SYNTAX Bitrate
			MAX-ACCESS read-only
			STATUS current
			DESCRIPTION
				"Bitrate null packets"
		::= { isw3000c01v1Entry 361 }

		-- 1.3.6.1.4.1.10106.3.101291.1.1.363
		isw3000c01v1Ts1PckNull OBJECT-TYPE
			SYNTAX PckNullRate1
			MAX-ACCESS read-only
			STATUS current
			DESCRIPTION
				"Packet null ratio"
		::= { isw3000c01v1Entry 363 }

		-- 1.3.6.1.4.1.10106.3.101291.1.1.365
		isw3000c01v1Ts2PckNull OBJECT-TYPE
			SYNTAX PckNullRate1
			MAX-ACCESS read-only
			STATUS current
			DESCRIPTION
				"Packet null ratio"
		::= { isw3000c01v1Entry 365 }

		-- 1.3.6.1.4.1.10106.3.101291.1.1.367
		isw3000c01v1BitrateErrorEn OBJECT-TYPE
			SYNTAX Bit0No1Yes
			MAX-ACCESS read-write
			STATUS current
			DESCRIPTION
				"Enables bitrate level error detection"
		::= { isw3000c01v1Entry 367 }

		-- 1.3.6.1.4.1.10106.3.101291.1.1.369
		isw3000c01v1NullPckErrEn OBJECT-TYPE
			SYNTAX Bit0No1Yes
			MAX-ACCESS read-write
			STATUS current
			DESCRIPTION
				"Enables null packets percentage error detection"
		::= { isw3000c01v1Entry 369 }

		-- 1.3.6.1.4.1.10106.3.101291.1.1.371
		isw3000c01v1Ts1TraffFail OBJECT-TYPE
			SYNTAX BitFail
			MAX-ACCESS read-only
			STATUS current
			DESCRIPTION
				"Bitrate status"
		::= { isw3000c01v1Entry 371 }

		-- 1.3.6.1.4.1.10106.3.101291.1.1.372
		isw3000c01v1Ts1TraffFailTrapEnable OBJECT-TYPE
			SYNTAX AlarmEnable
			MAX-ACCESS read-write
			STATUS current
			DESCRIPTION
				"Bitrate status Trap Enable"
		::= { isw3000c01v1Entry 372 }

		-- 1.3.6.1.4.1.10106.3.101291.1.1.373
		isw3000c01v1Ts1NullPFail OBJECT-TYPE
			SYNTAX BitFail
			MAX-ACCESS read-only
			STATUS current
			DESCRIPTION
				"Null packet rate status"
		::= { isw3000c01v1Entry 373 }

		-- 1.3.6.1.4.1.10106.3.101291.1.1.374
		isw3000c01v1Ts1NullPFailTrapEnable OBJECT-TYPE
			SYNTAX AlarmEnable
			MAX-ACCESS read-write
			STATUS current
			DESCRIPTION
				"Null packet rate status Trap Enable"
		::= { isw3000c01v1Entry 374 }

		-- 1.3.6.1.4.1.10106.3.101291.1.1.375
		isw3000c01v1Ts2TraffFail OBJECT-TYPE
			SYNTAX BitFail
			MAX-ACCESS read-only
			STATUS current
			DESCRIPTION
				"Bitrate status"
		::= { isw3000c01v1Entry 375 }

		-- 1.3.6.1.4.1.10106.3.101291.1.1.376
		isw3000c01v1Ts2TraffFailTrapEnable OBJECT-TYPE
			SYNTAX AlarmEnable
			MAX-ACCESS read-write
			STATUS current
			DESCRIPTION
				"Bitrate status Trap Enable"
		::= { isw3000c01v1Entry 376 }

		-- 1.3.6.1.4.1.10106.3.101291.1.1.377
		isw3000c01v1Ts2NullPFail OBJECT-TYPE
			SYNTAX BitFail
			MAX-ACCESS read-only
			STATUS current
			DESCRIPTION
				"Null packet rate status"
		::= { isw3000c01v1Entry 377 }

		-- 1.3.6.1.4.1.10106.3.101291.1.1.378
		isw3000c01v1Ts2NullPFailTrapEnable OBJECT-TYPE
			SYNTAX AlarmEnable
			MAX-ACCESS read-write
			STATUS current
			DESCRIPTION
				"Null packet rate status Trap Enable"
		::= { isw3000c01v1Entry 378 }

		-- 1.3.6.1.4.1.10106.3.101291.1.1.379
		isw3000c01v1PidSyncMode OBJECT-TYPE
			SYNTAX DvbT2SyncMode
			MAX-ACCESS read-write
			STATUS current
			DESCRIPTION
				"DVB-T2 synchronization mode (Timestamp PID detection)"
		::= { isw3000c01v1Entry 379 }

		-- 1.3.6.1.4.1.10106.3.101291.1.1.381
		isw3000c01v1PidSync OBJECT-TYPE
			SYNTAX Uint13
			MAX-ACCESS read-write
			STATUS current
			DESCRIPTION
				"Timestamp PID"
		::= { isw3000c01v1Entry 381 }

		-- 1.3.6.1.4.1.10106.3.101291.1.1.383
		isw3000c01v1GlobalError1G OBJECT-TYPE
			SYNTAX BitFail
			MAX-ACCESS read-only
			STATUS current
			DESCRIPTION
				"Global fail TS 1"
		::= { isw3000c01v1Entry 383 }

		-- 1.3.6.1.4.1.10106.3.101291.1.1.385
		isw3000c01v1GlobalError2G OBJECT-TYPE
			SYNTAX BitFail
			MAX-ACCESS read-only
			STATUS current
			DESCRIPTION
				"Global fail TS 2"
		::= { isw3000c01v1Entry 385 }

		-- 1.3.6.1.4.1.10106.3.101291.1.1.387
		isw3000c01v1LeapSecRd0 OBJECT-TYPE
			SYNTAX Uint8
			MAX-ACCESS read-only
			STATUS current
			DESCRIPTION
				"Leap seconds read"
		::= { isw3000c01v1Entry 387 }

		-- 1.3.6.1.4.1.10106.3.101291.1.1.389
		isw3000c01v1LeapSecRd1 OBJECT-TYPE
			SYNTAX Uint8
			MAX-ACCESS read-only
			STATUS current
			DESCRIPTION
				"Leap seconds read"
		::= { isw3000c01v1Entry 389 }

		-- 1.3.6.1.4.1.10106.3.101291.1.1.391
		isw3000c01v1MaxTimeOut OBJECT-TYPE
			SYNTAX TimeX1Ms1
			MAX-ACCESS read-write
			STATUS current
			DESCRIPTION
				"Maximum time out for IP channels without receiving any packet.  It limits the low frequency jitter capacity."
		::= { isw3000c01v1Entry 391 }

		-- 1.3.6.1.4.1.10106.3.101291.1.1.393
		isw3000c01v1OutDelayT2 OBJECT-TYPE
			SYNTAX DelayPacket2
			MAX-ACCESS read-write
			STATUS current
			DESCRIPTION
				"Output delay in TS packets in DVB-T2 mode with null timestamp"
		::= { isw3000c01v1Entry 393 }

		-- 1.3.6.1.4.1.10106.3.101291.1.1.394
		isw3000c01v1OutDelayT2TrapEnable OBJECT-TYPE
			SYNTAX AlarmEnable
			MAX-ACCESS read-write
			STATUS current
			DESCRIPTION
				"Output delay in TS packets in DVB-T2 mode with null timestamp Trap Enable"
		::= { isw3000c01v1Entry 394 }

		-- 1.3.6.1.4.1.10106.3.101291.1.1.395
		isw3000c01v1PatErrorTime OBJECT-TYPE
			SYNTAX TimeX1Ms1
			MAX-ACCESS read-write
			STATUS current
			DESCRIPTION
				"PAT error time out"
		::= { isw3000c01v1Entry 395 }

		-- 1.3.6.1.4.1.10106.3.101291.1.1.397
		isw3000c01v1PmtErrorTime OBJECT-TYPE
			SYNTAX TimeX1Ms1
			MAX-ACCESS read-write
			STATUS current
			DESCRIPTION
				"PMT error time out"
		::= { isw3000c01v1Entry 397 }

		-- 1.3.6.1.4.1.10106.3.101291.1.1.399
		isw3000c01v1MaxDelayTxIp OBJECT-TYPE
			SYNTAX TimeX10Ms
			MAX-ACCESS read-write
			STATUS current
			DESCRIPTION
				"Time before starting to transmit after recovering signal"
		::= { isw3000c01v1Entry 399 }

		-- 1.3.6.1.4.1.10106.3.101291.1.1.401
		isw3000c01v1InpFailMode OBJECT-TYPE
			SYNTAX Bit0Yes1No
			MAX-ACCESS read-write
			STATUS current
			DESCRIPTION
				"Selects if the output is muted when all the inputs fail"
		::= { isw3000c01v1Entry 401 }

		-- 1.3.6.1.4.1.10106.3.520302
		isw3000c01v2 OBJECT IDENTIFIER ::= { albalaProducts 520302 }

		-- 1.3.6.1.4.1.10106.3.520302.1
		isw3000c01v2Table  OBJECT-TYPE
			SYNTAX SEQUENCE OF Isw3000c01v2Entry
			MAX-ACCESS not-accessible
			STATUS current
			DESCRIPTION
				"Module  ISW3000C01V2 Table"
			::= { isw3000c01v2 1 }

		-- 1.3.6.1.4.1.10106.3.520302.1.1
		isw3000c01v2Entry  OBJECT-TYPE
			SYNTAX Isw3000c01v2Entry
			MAX-ACCESS not-accessible
			STATUS current
			DESCRIPTION
				"Module ISW3000C01V2 Entry"
			INDEX { isw3000c01v2Index }
			::= { isw3000c01v2Table 1 }

			Isw3000c01v2Entry ::=
			SEQUENCE {
				isw3000c01v2Index
				ModuleIndex,
				isw3000c01v2Mode
				ChgOverMode2,
				isw3000c01v2ModeTrapEnable
				AlarmEnable,
				isw3000c01v2DvbTMode
				DvbTModeIsw,
				isw3000c01v2DvbTModeTrapEnable
				AlarmEnable,
				isw3000c01v2NarrowPllBw
				Bit0No1Yes,
				isw3000c01v2Buzzer
				BitMask,
				isw3000c01v2NullPckRtp
				Bit0No1Yes,
				isw3000c01v2EnSeamNondvbt
				Bit0No1Yes,
				isw3000c01v2Input
				ChgOverIn2T,
				isw3000c01v2InputTrapEnable
				AlarmEnable,
				isw3000c01v2InputStChange
				Bit0No1Yes,
				isw3000c01v2InputChange
				Bit0No1Yes,
				isw3000c01v2OutDelay
				DelayX100Ns,
				isw3000c01v2OutDelayTrapEnable
				AlarmEnable,
				isw3000c01v2AsiMainPrior
				Uint1,
				isw3000c01v2AsiMainPriorTrapEnable
				AlarmEnable,
				isw3000c01v2AsiResPrior
				Uint1,
				isw3000c01v2AsiResPriorTrapEnable
				AlarmEnable,
				isw3000c01v2StatReset
				Bit0No1Yes,
				isw3000c01v2StatSel
				Bit0Ipm1Ipr,
				isw3000c01v2StatMode
				Bit01s1Total,
				isw3000c01v2IgmpVersion
				Bit0V21V3,
				isw3000c01v2EthMode
				EthMode,
				isw3000c01v2PingEnable
				Bit0No1Yes,
				isw3000c01v2SpeedForce
				Bit0Ann1For,
				isw3000c01v2OutDelayT2
				DelayPacket2,
				isw3000c01v2OutDelayT2TrapEnable
				AlarmEnable,
				isw3000c01v2PacketDelay
				DelayPacket2,
				isw3000c01v2PacketDelayTrapEnable
				AlarmEnable,
				isw3000c01v2IpLinkFailEn
				Bit0No1Yes,
				isw3000c01v2IpDestFailEn
				Bit0No1Yes,
				isw3000c01v2TsSyncLossEn
				Bit0No1Yes,
				isw3000c01v2SyncByErrorEn
				Bit0No1Yes,
				isw3000c01v2PatErrorEn
				Bit0No1Yes,
				isw3000c01v2CcErrorEn
				Bit0No1Yes,
				isw3000c01v2PmtErrorEn
				Bit0No1Yes,
				isw3000c01v2PidErrorEn
				Bit0No1Yes,
				isw3000c01v2BitrateErrorEn
				Bit0No1Yes,
				isw3000c01v2NullPckErrEn
				Bit0No1Yes,
				isw3000c01v2PidErrorTime
				TimeX1Ms1,
				isw3000c01v2Ch1Selection
				IswChSelection,
				isw3000c01v2Ch1SelectionTrapEnable
				AlarmEnable,
				isw3000c01v2Ch2Selection
				IswChSelection,
				isw3000c01v2Ch2SelectionTrapEnable
				AlarmEnable,
				isw3000c01v2MaxTimeOut
				TimeX1Ms1,
				isw3000c01v2OutDelay0
				DelayX1S127,
				isw3000c01v2OutDelay0TrapEnable
				AlarmEnable,
				isw3000c01v2OutDelay1
				DelayX100Ns,
				isw3000c01v2OutDelay1TrapEnable
				AlarmEnable,
				isw3000c01v2PidSyncMode
				DvbT2SyncMode,
				isw3000c01v2PidSync
				Uint13,
				isw3000c01v2PatErrorTime
				TimeX1Ms1,
				isw3000c01v2PmtErrorTime
				TimeX1Ms1,
				isw3000c01v2Str1UipDAdd3
				Uint8,
				isw3000c01v2Str1UipDAdd2
				Uint8,
				isw3000c01v2Str1UipDAdd1
				Uint8,
				isw3000c01v2Str1UipDAdd0
				Uint8,
				isw3000c01v2Str1MipDAdd3
				Uint8,
				isw3000c01v2Str1MipDAdd2
				Uint8,
				isw3000c01v2Str1MipDAdd1
				Uint8,
				isw3000c01v2Str1MipDAdd0
				Uint8,
				isw3000c01v2Str1DPortMsb
				Uint8,
				isw3000c01v2Str1DPortLsb
				Uint8,
				isw3000c01v2Str1FecEna
				Bit0No1Yes,
				isw3000c01v2Str1MulticEna
				IpaTxMode,
				isw3000c01v2VlanRx1Enable
				Bit0No1Yes,
				isw3000c01v2VlanRx1Reg1
				Uint8,
				isw3000c01v2VlanRx1Reg2
				Uint8,
				isw3000c01v2Str2UipDAdd3
				Uint8,
				isw3000c01v2Str2UipDAdd2
				Uint8,
				isw3000c01v2Str2UipDAdd1
				Uint8,
				isw3000c01v2Str2UipDAdd0
				Uint8,
				isw3000c01v2Str2MipDAdd3
				Uint8,
				isw3000c01v2Str2MipDAdd2
				Uint8,
				isw3000c01v2Str2MipDAdd1
				Uint8,
				isw3000c01v2Str2MipDAdd0
				Uint8,
				isw3000c01v2Str2DPortMsb
				Uint8,
				isw3000c01v2Str2DPortLsb
				Uint8,
				isw3000c01v2Str2FecEna
				Bit0No1Yes,
				isw3000c01v2Str2MulticEna
				IpaTxMode,
				isw3000c01v2VlanRx2Enable
				Bit0No1Yes,
				isw3000c01v2VlanRx2Reg1
				Uint8,
				isw3000c01v2VlanRx2Reg2
				Uint8,
				isw3000c01v2TxUniEna
				Bit0No1Yes,
				isw3000c01v2TxMultiEna
				IpaTxMode,
				isw3000c01v2LocalIpAdd3
				Uint8,
				isw3000c01v2LocalIpAdd2
				Uint8,
				isw3000c01v2LocalIpAdd1
				Uint8,
				isw3000c01v2LocalIpAdd0
				Uint8,
				isw3000c01v2LocalIpMask3
				Uint8,
				isw3000c01v2LocalIpMask2
				Uint8,
				isw3000c01v2LocalIpMask1
				Uint8,
				isw3000c01v2LocalIpMask0
				Uint8,
				isw3000c01v2LocalIpGway3
				Uint8,
				isw3000c01v2LocalIpGway2
				Uint8,
				isw3000c01v2LocalIpGway1
				Uint8,
				isw3000c01v2LocalIpGway0
				Uint8,
				isw3000c01v2TxUipAdd3
				Uint8,
				isw3000c01v2TxUipAdd2
				Uint8,
				isw3000c01v2TxUipAdd1
				Uint8,
				isw3000c01v2TxUipAdd0
				Uint8,
				isw3000c01v2TxMipAdd3
				Uint8,
				isw3000c01v2TxMipAdd2
				Uint8,
				isw3000c01v2TxMipAdd1
				Uint8,
				isw3000c01v2TxMipAdd0
				Uint8,
				isw3000c01v2TxSPortMsb
				Uint8,
				isw3000c01v2TxSPortLsb
				Uint8,
				isw3000c01v2TxDPortMsb
				Uint8,
				isw3000c01v2TxDPortLsb
				Uint8,
				isw3000c01v2VlanTxEnable
				Bit0No1Yes,
				isw3000c01v2VlanTxPriority
				Uint3,
				isw3000c01v2VlanTxReg1
				Uint8,
				isw3000c01v2VlanTxReg2
				Uint8,
				isw3000c01v2TxLParam
				Uint5,
				isw3000c01v2TxFecMode
				FecMode,
				isw3000c01v2TxDParam
				Uint5,
				isw3000c01v2TxTspkInIppk
				Uint3,
				isw3000c01v2TxRowDelay
				Uint5,
				isw3000c01v2TxColDelay
				Uint8,
				isw3000c01v2LowCost
				Bit0No1Yes,
				isw3000c01v2HighReliabilty
				Bit0No1Yes,
				isw3000c01v2HighThroughput
				Bit0No1Yes,
				isw3000c01v2LowDelay
				Bit0No1Yes,
				isw3000c01v2Precedence
				IpaPrecedence,
				isw3000c01v2Ttl
				Uint8,
				isw3000c01v2Str1IgmFAdd3
				Uint8,
				isw3000c01v2Str1IgmFAdd2
				Uint8,
				isw3000c01v2Str1IgmFAdd1
				Uint8,
				isw3000c01v2Str1IgmFAdd0
				Uint8,
				isw3000c01v2Str2IgmFAdd3
				Uint8,
				isw3000c01v2Str2IgmFAdd2
				Uint8,
				isw3000c01v2Str2IgmFAdd1
				Uint8,
				isw3000c01v2Str2IgmFAdd0
				Uint8,
				isw3000c01v2MaxBitrateNull
				Bitrate,
				isw3000c01v2MinBitrateNull
				Bitrate,
				isw3000c01v2PckNullMax
				PckNullRate1,
				isw3000c01v2PckNullMin
				PckNullRate1,
				isw3000c01v2DvbT2Lock1
				DvbT2Locked,
				isw3000c01v2DvbT2Lock1TrapEnable
				AlarmEnable,
				isw3000c01v2DvbT2Lock2
				DvbT2Locked,
				isw3000c01v2DvbT2Lock2TrapEnable
				AlarmEnable,
				isw3000c01v2Ts1DelayExt
				DelayX02Ms,
				isw3000c01v2Ts2DelayExt
				DelayX02Ms,
				isw3000c01v2DelayT20S
				DelayX1S,
				isw3000c01v2DelayT20Ms
				DelayX100Ns,
				isw3000c01v2DelayT21S
				DelayX1S,
				isw3000c01v2DelayT21Ms
				DelayX100Ns,
				isw3000c01v2Bitrate1
				Bitrate,
				isw3000c01v2Bitrate2
				Bitrate,
				isw3000c01v2BitrateNull1
				Bitrate,
				isw3000c01v2BitrateNull2
				Bitrate,
				isw3000c01v2Ts1PckNull
				PckNullRate1,
				isw3000c01v2Ts2PckNull
				PckNullRate1,
				isw3000c01v2Ts1TraffFail
				BitFail,
				isw3000c01v2Ts1TraffFailTrapEnable
				AlarmEnable,
				isw3000c01v2Ts1NullPFail
				BitFail,
				isw3000c01v2Ts1NullPFailTrapEnable
				AlarmEnable,
				isw3000c01v2Ts2TraffFail
				BitFail,
				isw3000c01v2Ts2TraffFailTrapEnable
				AlarmEnable,
				isw3000c01v2Ts2NullPFail
				BitFail,
				isw3000c01v2Ts2NullPFailTrapEnable
				AlarmEnable,
				isw3000c01v21ppsFail
				BitFail,
				isw3000c01v21ppsFailTrapEnable
				AlarmEnable,
				isw3000c01v210mhzFail
				BitFail,
				isw3000c01v210mhzFailTrapEnable
				AlarmEnable,
				isw3000c01v2OutputFail
				BitFail,
				isw3000c01v2OutputFailTrapEnable
				AlarmEnable,
				isw3000c01v2Ts1DelWar
				BitFail,
				isw3000c01v2Ts1DelWarTrapEnable
				AlarmEnable,
				isw3000c01v2Ts2DelWar
				BitFail,
				isw3000c01v2Ts2DelWarTrapEnable
				AlarmEnable,
				isw3000c01v2ExtFail1
				BitFail,
				isw3000c01v2ExtFail1TrapEnable
				AlarmEnable,
				isw3000c01v2ExtFail2
				BitFail,
				isw3000c01v2ExtFail2TrapEnable
				AlarmEnable,
				isw3000c01v2GlobalSeam
				Bit0Sea1Nse,
				isw3000c01v2GlobalSeamTrapEnable
				AlarmEnable,
				isw3000c01v2SyncLossErr1
				BitFail,
				isw3000c01v2SyncLossErr1TrapEnable
				AlarmEnable,
				isw3000c01v2SyncByteErr1
				BitFail,
				isw3000c01v2SyncByteErr1TrapEnable
				AlarmEnable,
				isw3000c01v2PatError1
				BitFail,
				isw3000c01v2PatError1TrapEnable
				AlarmEnable,
				isw3000c01v2CcError1
				BitFail,
				isw3000c01v2CcError1TrapEnable
				AlarmEnable,
				isw3000c01v2PmtError1
				BitFail,
				isw3000c01v2PmtError1TrapEnable
				AlarmEnable,
				isw3000c01v2PidError1
				BitFail,
				isw3000c01v2PidError1TrapEnable
				AlarmEnable,
				isw3000c01v2MipError1
				BitFail,
				isw3000c01v2MipError1TrapEnable
				AlarmEnable,
				isw3000c01v2GlobalError1
				BitFail,
				isw3000c01v2GlobalError1TrapEnable
				AlarmEnable,
				isw3000c01v2GlobalError1G
				BitFail,
				isw3000c01v2SyncLossErr2
				BitFail,
				isw3000c01v2SyncLossErr2TrapEnable
				AlarmEnable,
				isw3000c01v2SyncByteErr2
				BitFail,
				isw3000c01v2SyncByteErr2TrapEnable
				AlarmEnable,
				isw3000c01v2PatError2
				BitFail,
				isw3000c01v2PatError2TrapEnable
				AlarmEnable,
				isw3000c01v2CcError2
				BitFail,
				isw3000c01v2CcError2TrapEnable
				AlarmEnable,
				isw3000c01v2PmtError2
				BitFail,
				isw3000c01v2PmtError2TrapEnable
				AlarmEnable,
				isw3000c01v2PidError2
				BitFail,
				isw3000c01v2PidError2TrapEnable
				AlarmEnable,
				isw3000c01v2MipError2
				BitFail,
				isw3000c01v2MipError2TrapEnable
				AlarmEnable,
				isw3000c01v2GlobalError2
				BitFail,
				isw3000c01v2GlobalError2TrapEnable
				AlarmEnable,
				isw3000c01v2GlobalError2G
				BitFail,
				isw3000c01v2IpRxAddress3
				Uint8,
				isw3000c01v2IpRxAddress2
				Uint8,
				isw3000c01v2IpRxAddress1
				Uint8,
				isw3000c01v2IpRxAddress0
				Uint8,
				isw3000c01v2IpRxPort
				Uint16,
				isw3000c01v2LParam
				Uint5,
				isw3000c01v2FecMode
				FecMode,
				isw3000c01v2PacketSize
				Bit02041188,
				isw3000c01v2DParam
				Uint5,
				isw3000c01v2TsPckInIpPck
				Uint3,
				isw3000c01v2PacketRate
				PacketRate,
				isw3000c01v2TimeSinceReset
				TimeS4,
				isw3000c01v2LostIpPck
				Uint16,
				isw3000c01v2RecoveredIpPck
				Uint16,
				isw3000c01v2BadCrcPck
				Uint16,
				isw3000c01v2OutOrdIpPck
				Uint16,
				isw3000c01v2FecRate
				PacketRate,
				isw3000c01v2Link
				IpaEtherStat,
				isw3000c01v2System
				IpaEtherSys,
				isw3000c01v2DestAvailable
				Bit0No1Yes,
				isw3000c01v2Ts1BufOvf
				BitFail,
				isw3000c01v2Ts2BufOvf
				BitFail,
				isw3000c01v2Ts1BufUnd
				BitFail,
				isw3000c01v2Ts2BufUnd
				BitFail,
				isw3000c01v2BufferStatus
				Rate1,
				isw3000c01v2PingStatus
				IpaPingStat,
				isw3000c01v2SerialNo
				SerialNo,
				isw3000c01v2MaxDelayTxIp
				TimeX10Ms,
				isw3000c01v2InpFailMode
				Bit0Yes1No
			 }

		-- 1.3.6.1.4.1.10106.3.101291.1.1.1
		isw3000c01v2Index OBJECT-TYPE
			SYNTAX ModuleIndex
			MAX-ACCESS read-only
			STATUS current
			DESCRIPTION
				"Index of ISW3000C01V2 Table"
		::= { isw3000c01v2Entry 1 }

		-- 1.3.6.1.4.1.10106.3.101291.1.1.3
		isw3000c01v2Mode OBJECT-TYPE
			SYNTAX ChgOverMode2
			MAX-ACCESS read-write
			STATUS current
			DESCRIPTION
				"Allows selecting the switching mode"
		::= { isw3000c01v2Entry 3 }

		-- 1.3.6.1.4.1.10106.3.101291.1.1.4
		isw3000c01v2ModeTrapEnable OBJECT-TYPE
			SYNTAX AlarmEnable
			MAX-ACCESS read-write
			STATUS current
			DESCRIPTION
				"Allows selecting the switching mode Trap Enable"
		::= { isw3000c01v2Entry 4 }

		-- 1.3.6.1.4.1.10106.3.101291.1.1.5
		isw3000c01v2DvbTMode OBJECT-TYPE
			SYNTAX DvbTModeIsw
			MAX-ACCESS read-write
			STATUS current
			DESCRIPTION
				"Selects DVB mode."
		::= { isw3000c01v2Entry 5 }

		-- 1.3.6.1.4.1.10106.3.101291.1.1.6
		isw3000c01v2DvbTModeTrapEnable OBJECT-TYPE
			SYNTAX AlarmEnable
			MAX-ACCESS read-write
			STATUS current
			DESCRIPTION
				"Selects DVB mode. Trap Enable"
		::= { isw3000c01v2Entry 6 }

		-- 1.3.6.1.4.1.10106.3.101291.1.1.7
		isw3000c01v2NarrowPllBw OBJECT-TYPE
			SYNTAX Bit0No1Yes
			MAX-ACCESS read-write
			STATUS current
			DESCRIPTION
				"Allows selecting a narrow PLL bandwidth in the clock packet PLL in Generic DVB modeto achieve a very stable bitrate"
		::= { isw3000c01v2Entry 7 }

		-- 1.3.6.1.4.1.10106.3.101291.1.1.9
		isw3000c01v2Buzzer OBJECT-TYPE
			SYNTAX BitMask
			MAX-ACCESS read-write
			STATUS current
			DESCRIPTION
				"Allows buzzer operation"
		::= { isw3000c01v2Entry 9 }

		-- 1.3.6.1.4.1.10106.3.101291.1.1.11
		isw3000c01v2NullPckRtp OBJECT-TYPE
			SYNTAX Bit0No1Yes
			MAX-ACCESS read-write
			STATUS current
			DESCRIPTION
				"Selects if NULL packets are inserted if there are unrecovered packets when using RTP protocol"
		::= { isw3000c01v2Entry 11 }

		-- 1.3.6.1.4.1.10106.3.101291.1.1.13
		isw3000c01v2EnSeamNondvbt OBJECT-TYPE
			SYNTAX Bit0No1Yes
			MAX-ACCESS read-write
			STATUS current
			DESCRIPTION
				"Allows enabling seamless mode with in Generic DVB mode"
		::= { isw3000c01v2Entry 13 }

		-- 1.3.6.1.4.1.10106.3.101291.1.1.15
		isw3000c01v2Input OBJECT-TYPE
			SYNTAX ChgOverIn2T
			MAX-ACCESS read-write
			STATUS current
			DESCRIPTION
				"Selected TS"
		::= { isw3000c01v2Entry 15 }

		-- 1.3.6.1.4.1.10106.3.101291.1.1.16
		isw3000c01v2InputTrapEnable OBJECT-TYPE
			SYNTAX AlarmEnable
			MAX-ACCESS read-write
			STATUS current
			DESCRIPTION
				"Selected TS Trap Enable"
		::= { isw3000c01v2Entry 16 }

		-- 1.3.6.1.4.1.10106.3.101291.1.1.17
		isw3000c01v2InputStChange OBJECT-TYPE
			SYNTAX Bit0No1Yes
			MAX-ACCESS read-write
			STATUS current
			DESCRIPTION
				"Signals a change in fail status"
		::= { isw3000c01v2Entry 17 }

		-- 1.3.6.1.4.1.10106.3.101291.1.1.19
		isw3000c01v2InputChange OBJECT-TYPE
			SYNTAX Bit0No1Yes
			MAX-ACCESS read-write
			STATUS current
			DESCRIPTION
				"Signals a change in selected input"
		::= { isw3000c01v2Entry 19 }

		-- 1.3.6.1.4.1.10106.3.101291.1.1.21
		isw3000c01v2OutDelay OBJECT-TYPE
			SYNTAX DelayX100Ns
			MAX-ACCESS read-write
			STATUS current
			DESCRIPTION
				"Output delay refered to 1PPS reference in DVB-T mode"
		::= { isw3000c01v2Entry 21 }

		-- 1.3.6.1.4.1.10106.3.101291.1.1.22
		isw3000c01v2OutDelayTrapEnable OBJECT-TYPE
			SYNTAX AlarmEnable
			MAX-ACCESS read-write
			STATUS current
			DESCRIPTION
				"Output delay refered to 1PPS reference in DVB-T mode Trap Enable"
		::= { isw3000c01v2Entry 22 }

		-- 1.3.6.1.4.1.10106.3.101291.1.1.23
		isw3000c01v2AsiMainPrior OBJECT-TYPE
			SYNTAX Uint1
			MAX-ACCESS read-write
			STATUS current
			DESCRIPTION
				"Allows selecting the ASI main input priority"
		::= { isw3000c01v2Entry 23 }

		-- 1.3.6.1.4.1.10106.3.101291.1.1.24
		isw3000c01v2AsiMainPriorTrapEnable OBJECT-TYPE
			SYNTAX AlarmEnable
			MAX-ACCESS read-write
			STATUS current
			DESCRIPTION
				"Allows selecting the ASI main input priority Trap Enable"
		::= { isw3000c01v2Entry 24 }

		-- 1.3.6.1.4.1.10106.3.101291.1.1.25
		isw3000c01v2AsiResPrior OBJECT-TYPE
			SYNTAX Uint1
			MAX-ACCESS read-write
			STATUS current
			DESCRIPTION
				"Allows selecting the ASI reserve input priority"
		::= { isw3000c01v2Entry 25 }

		-- 1.3.6.1.4.1.10106.3.101291.1.1.26
		isw3000c01v2AsiResPriorTrapEnable OBJECT-TYPE
			SYNTAX AlarmEnable
			MAX-ACCESS read-write
			STATUS current
			DESCRIPTION
				"Allows selecting the ASI reserve input priority Trap Enable"
		::= { isw3000c01v2Entry 26 }

		-- 1.3.6.1.4.1.10106.3.101291.1.1.27
		isw3000c01v2StatReset OBJECT-TYPE
			SYNTAX Bit0No1Yes
			MAX-ACCESS read-write
			STATUS current
			DESCRIPTION
				"Allows reseting the statistics measurements"
		::= { isw3000c01v2Entry 27 }

		-- 1.3.6.1.4.1.10106.3.101291.1.1.29
		isw3000c01v2StatSel OBJECT-TYPE
			SYNTAX Bit0Ipm1Ipr
			MAX-ACCESS read-write
			STATUS current
			DESCRIPTION
				"Allows selecting the channel to be displayed"
		::= { isw3000c01v2Entry 29 }

		-- 1.3.6.1.4.1.10106.3.101291.1.1.31
		isw3000c01v2StatMode OBJECT-TYPE
			SYNTAX Bit01s1Total
			MAX-ACCESS read-write
			STATUS current
			DESCRIPTION
				"Allows selecting the statistics mode"
		::= { isw3000c01v2Entry 31 }

		-- 1.3.6.1.4.1.10106.3.101291.1.1.33
		isw3000c01v2IgmpVersion OBJECT-TYPE
			SYNTAX Bit0V21V3
			MAX-ACCESS read-write
			STATUS current
			DESCRIPTION
				"Allows selecting the IGMP version"
		::= { isw3000c01v2Entry 33 }

		-- 1.3.6.1.4.1.10106.3.101291.1.1.35
		isw3000c01v2EthMode OBJECT-TYPE
			SYNTAX EthMode
			MAX-ACCESS read-write
			STATUS current
			DESCRIPTION
				"Allows selecting the Ethernet operating mode"
		::= { isw3000c01v2Entry 35 }

		-- 1.3.6.1.4.1.10106.3.101291.1.1.37
		isw3000c01v2PingEnable OBJECT-TYPE
			SYNTAX Bit0No1Yes
			MAX-ACCESS read-write
			STATUS current
			DESCRIPTION
				"Allows making a periodic ping to the unicast address"
		::= { isw3000c01v2Entry 37 }

		-- 1.3.6.1.4.1.10106.3.101291.1.1.39
		isw3000c01v2SpeedForce OBJECT-TYPE
			SYNTAX Bit0Ann1For
			MAX-ACCESS read-write
			STATUS current
			DESCRIPTION
				"Allows selecting if the speed/mode is forced or announced for autonegotiation"
		::= { isw3000c01v2Entry 39 }

		-- 1.3.6.1.4.1.10106.3.101291.1.1.41
		isw3000c01v2OutDelayT2 OBJECT-TYPE
			SYNTAX DelayPacket2
			MAX-ACCESS read-write
			STATUS current
			DESCRIPTION
				"Output delay in TS packets in DVB-T2 mode with null timestamp"
		::= { isw3000c01v2Entry 41 }

		-- 1.3.6.1.4.1.10106.3.101291.1.1.42
		isw3000c01v2OutDelayT2TrapEnable OBJECT-TYPE
			SYNTAX AlarmEnable
			MAX-ACCESS read-write
			STATUS current
			DESCRIPTION
				"Output delay in TS packets in DVB-T2 mode with null timestamp Trap Enable"
		::= { isw3000c01v2Entry 42 }

		-- 1.3.6.1.4.1.10106.3.101291.1.1.43
		isw3000c01v2PacketDelay OBJECT-TYPE
			SYNTAX DelayPacket2
			MAX-ACCESS read-write
			STATUS current
			DESCRIPTION
				"Output delay in TS packets in Generic DVB mode"
		::= { isw3000c01v2Entry 43 }

		-- 1.3.6.1.4.1.10106.3.101291.1.1.44
		isw3000c01v2PacketDelayTrapEnable OBJECT-TYPE
			SYNTAX AlarmEnable
			MAX-ACCESS read-write
			STATUS current
			DESCRIPTION
				"Output delay in TS packets in Generic DVB mode Trap Enable"
		::= { isw3000c01v2Entry 44 }

		-- 1.3.6.1.4.1.10106.3.101291.1.1.45
		isw3000c01v2IpLinkFailEn OBJECT-TYPE
			SYNTAX Bit0No1Yes
			MAX-ACCESS read-write
			STATUS current
			DESCRIPTION
				"IP link lose signals fail in F_OUT GPO"
		::= { isw3000c01v2Entry 45 }

		-- 1.3.6.1.4.1.10106.3.101291.1.1.47
		isw3000c01v2IpDestFailEn OBJECT-TYPE
			SYNTAX Bit0No1Yes
			MAX-ACCESS read-write
			STATUS current
			DESCRIPTION
				"IP destination absence signals fail in F_OUT GPO"
		::= { isw3000c01v2Entry 47 }

		-- 1.3.6.1.4.1.10106.3.101291.1.1.49
		isw3000c01v2TsSyncLossEn OBJECT-TYPE
			SYNTAX Bit0No1Yes
			MAX-ACCESS read-write
			STATUS current
			DESCRIPTION
				"Enables loss of synchronization detection (Fist priority  parameter 1.1)"
		::= { isw3000c01v2Entry 49 }

		-- 1.3.6.1.4.1.10106.3.101291.1.1.51
		isw3000c01v2SyncByErrorEn OBJECT-TYPE
			SYNTAX Bit0No1Yes
			MAX-ACCESS read-write
			STATUS current
			DESCRIPTION
				"Enables sync byte error detection (Fist priority  parameter 1.2)"
		::= { isw3000c01v2Entry 51 }

		-- 1.3.6.1.4.1.10106.3.101291.1.1.53
		isw3000c01v2PatErrorEn OBJECT-TYPE
			SYNTAX Bit0No1Yes
			MAX-ACCESS read-write
			STATUS current
			DESCRIPTION
				"Enables PAT error detection (Fist priority  parameter 1.3)"
		::= { isw3000c01v2Entry 53 }

		-- 1.3.6.1.4.1.10106.3.101291.1.1.55
		isw3000c01v2CcErrorEn OBJECT-TYPE
			SYNTAX Bit0No1Yes
			MAX-ACCESS read-write
			STATUS current
			DESCRIPTION
				"Enables continuity counter error detection (Fist priority  parameter 1.4)"
		::= { isw3000c01v2Entry 55 }

		-- 1.3.6.1.4.1.10106.3.101291.1.1.57
		isw3000c01v2PmtErrorEn OBJECT-TYPE
			SYNTAX Bit0No1Yes
			MAX-ACCESS read-write
			STATUS current
			DESCRIPTION
				"Enables PMT error detection (Fist priority  parameter 1.5)"
		::= { isw3000c01v2Entry 57 }

		-- 1.3.6.1.4.1.10106.3.101291.1.1.59
		isw3000c01v2PidErrorEn OBJECT-TYPE
			SYNTAX Bit0No1Yes
			MAX-ACCESS read-write
			STATUS current
			DESCRIPTION
				"Enables PID error detection (Fist priority  parameter 1.6)"
		::= { isw3000c01v2Entry 59 }

		-- 1.3.6.1.4.1.10106.3.101291.1.1.61
		isw3000c01v2BitrateErrorEn OBJECT-TYPE
			SYNTAX Bit0No1Yes
			MAX-ACCESS read-write
			STATUS current
			DESCRIPTION
				"Enables bitrate level error detection"
		::= { isw3000c01v2Entry 61 }

		-- 1.3.6.1.4.1.10106.3.101291.1.1.63
		isw3000c01v2NullPckErrEn OBJECT-TYPE
			SYNTAX Bit0No1Yes
			MAX-ACCESS read-write
			STATUS current
			DESCRIPTION
				"Enables null packets percentage error detection"
		::= { isw3000c01v2Entry 63 }

		-- 1.3.6.1.4.1.10106.3.101291.1.1.65
		isw3000c01v2PidErrorTime OBJECT-TYPE
			SYNTAX TimeX1Ms1
			MAX-ACCESS read-write
			STATUS current
			DESCRIPTION
				"PID error time out"
		::= { isw3000c01v2Entry 65 }

		-- 1.3.6.1.4.1.10106.3.101291.1.1.67
		isw3000c01v2Ch1Selection OBJECT-TYPE
			SYNTAX IswChSelection
			MAX-ACCESS read-write
			STATUS current
			DESCRIPTION
				"Channel 1 input selection"
		::= { isw3000c01v2Entry 67 }

		-- 1.3.6.1.4.1.10106.3.101291.1.1.68
		isw3000c01v2Ch1SelectionTrapEnable OBJECT-TYPE
			SYNTAX AlarmEnable
			MAX-ACCESS read-write
			STATUS current
			DESCRIPTION
				"Channel 1 input selection Trap Enable"
		::= { isw3000c01v2Entry 68 }

		-- 1.3.6.1.4.1.10106.3.101291.1.1.69
		isw3000c01v2Ch2Selection OBJECT-TYPE
			SYNTAX IswChSelection
			MAX-ACCESS read-write
			STATUS current
			DESCRIPTION
				"Channel 2 input selection"
		::= { isw3000c01v2Entry 69 }

		-- 1.3.6.1.4.1.10106.3.101291.1.1.70
		isw3000c01v2Ch2SelectionTrapEnable OBJECT-TYPE
			SYNTAX AlarmEnable
			MAX-ACCESS read-write
			STATUS current
			DESCRIPTION
				"Channel 2 input selection Trap Enable"
		::= { isw3000c01v2Entry 70 }

		-- 1.3.6.1.4.1.10106.3.101291.1.1.71
		isw3000c01v2MaxTimeOut OBJECT-TYPE
			SYNTAX TimeX1Ms1
			MAX-ACCESS read-write
			STATUS current
			DESCRIPTION
				"Maximum time out for IP channels without receiving any packet.  It limits the low frequency jitter capacity."
		::= { isw3000c01v2Entry 71 }

		-- 1.3.6.1.4.1.10106.3.101291.1.1.73
		isw3000c01v2OutDelay0 OBJECT-TYPE
			SYNTAX DelayX1S127
			MAX-ACCESS read-write
			STATUS current
			DESCRIPTION
				"Output time in advance refered to 1PPS or absolute time reference in DVB-T2 mode.  Seconds."
		::= { isw3000c01v2Entry 73 }

		-- 1.3.6.1.4.1.10106.3.101291.1.1.74
		isw3000c01v2OutDelay0TrapEnable OBJECT-TYPE
			SYNTAX AlarmEnable
			MAX-ACCESS read-write
			STATUS current
			DESCRIPTION
				"Output time in advance refered to 1PPS or absolute time reference in DVB-T2 mode.  Seconds. Trap Enable"
		::= { isw3000c01v2Entry 74 }

		-- 1.3.6.1.4.1.10106.3.101291.1.1.75
		isw3000c01v2OutDelay1 OBJECT-TYPE
			SYNTAX DelayX100Ns
			MAX-ACCESS read-write
			STATUS current
			DESCRIPTION
				"Output time in advance refered to 1PPS or absolute time reference in DVB-T2 mode.  Miliseconds."
		::= { isw3000c01v2Entry 75 }

		-- 1.3.6.1.4.1.10106.3.101291.1.1.76
		isw3000c01v2OutDelay1TrapEnable OBJECT-TYPE
			SYNTAX AlarmEnable
			MAX-ACCESS read-write
			STATUS current
			DESCRIPTION
				"Output time in advance refered to 1PPS or absolute time reference in DVB-T2 mode.  Miliseconds. Trap Enable"
		::= { isw3000c01v2Entry 76 }

		-- 1.3.6.1.4.1.10106.3.101291.1.1.77
		isw3000c01v2PidSyncMode OBJECT-TYPE
			SYNTAX DvbT2SyncMode
			MAX-ACCESS read-write
			STATUS current
			DESCRIPTION
				"DVB-T2 synchronization mode (Timestamp PID detection)"
		::= { isw3000c01v2Entry 77 }

		-- 1.3.6.1.4.1.10106.3.101291.1.1.79
		isw3000c01v2PidSync OBJECT-TYPE
			SYNTAX Uint13
			MAX-ACCESS read-write
			STATUS current
			DESCRIPTION
				"Timestamp PID"
		::= { isw3000c01v2Entry 79 }

		-- 1.3.6.1.4.1.10106.3.101291.1.1.81
		isw3000c01v2PatErrorTime OBJECT-TYPE
			SYNTAX TimeX1Ms1
			MAX-ACCESS read-write
			STATUS current
			DESCRIPTION
				"PAT error time out"
		::= { isw3000c01v2Entry 81 }

		-- 1.3.6.1.4.1.10106.3.101291.1.1.83
		isw3000c01v2PmtErrorTime OBJECT-TYPE
			SYNTAX TimeX1Ms1
			MAX-ACCESS read-write
			STATUS current
			DESCRIPTION
				"PMT error time out"
		::= { isw3000c01v2Entry 83 }

		-- 1.3.6.1.4.1.10106.3.101291.1.1.85
		isw3000c01v2Str1UipDAdd3 OBJECT-TYPE
			SYNTAX Uint8
			MAX-ACCESS read-write
			STATUS current
			DESCRIPTION
				"Unicast IP address (3)"
		::= { isw3000c01v2Entry 85 }

		-- 1.3.6.1.4.1.10106.3.101291.1.1.87
		isw3000c01v2Str1UipDAdd2 OBJECT-TYPE
			SYNTAX Uint8
			MAX-ACCESS read-write
			STATUS current
			DESCRIPTION
				"Unicast IP address (2)"
		::= { isw3000c01v2Entry 87 }

		-- 1.3.6.1.4.1.10106.3.101291.1.1.89
		isw3000c01v2Str1UipDAdd1 OBJECT-TYPE
			SYNTAX Uint8
			MAX-ACCESS read-write
			STATUS current
			DESCRIPTION
				"Unicast IP address (1)"
		::= { isw3000c01v2Entry 89 }

		-- 1.3.6.1.4.1.10106.3.101291.1.1.91
		isw3000c01v2Str1UipDAdd0 OBJECT-TYPE
			SYNTAX Uint8
			MAX-ACCESS read-write
			STATUS current
			DESCRIPTION
				"Unicast IP address (0)"
		::= { isw3000c01v2Entry 91 }

		-- 1.3.6.1.4.1.10106.3.101291.1.1.93
		isw3000c01v2Str1MipDAdd3 OBJECT-TYPE
			SYNTAX Uint8
			MAX-ACCESS read-write
			STATUS current
			DESCRIPTION
				"Multicast IP address (3)"
		::= { isw3000c01v2Entry 93 }

		-- 1.3.6.1.4.1.10106.3.101291.1.1.95
		isw3000c01v2Str1MipDAdd2 OBJECT-TYPE
			SYNTAX Uint8
			MAX-ACCESS read-write
			STATUS current
			DESCRIPTION
				"Multicast IP address (2)"
		::= { isw3000c01v2Entry 95 }

		-- 1.3.6.1.4.1.10106.3.101291.1.1.97
		isw3000c01v2Str1MipDAdd1 OBJECT-TYPE
			SYNTAX Uint8
			MAX-ACCESS read-write
			STATUS current
			DESCRIPTION
				"Multicast IP address (1)"
		::= { isw3000c01v2Entry 97 }

		-- 1.3.6.1.4.1.10106.3.101291.1.1.99
		isw3000c01v2Str1MipDAdd0 OBJECT-TYPE
			SYNTAX Uint8
			MAX-ACCESS read-write
			STATUS current
			DESCRIPTION
				"Multicast IP address (0)"
		::= { isw3000c01v2Entry 99 }

		-- 1.3.6.1.4.1.10106.3.101291.1.1.101
		isw3000c01v2Str1DPortMsb OBJECT-TYPE
			SYNTAX Uint8
			MAX-ACCESS read-write
			STATUS current
			DESCRIPTION
				"Destination port (msb)"
		::= { isw3000c01v2Entry 101 }

		-- 1.3.6.1.4.1.10106.3.101291.1.1.103
		isw3000c01v2Str1DPortLsb OBJECT-TYPE
			SYNTAX Uint8
			MAX-ACCESS read-write
			STATUS current
			DESCRIPTION
				"Destination port (lsb)"
		::= { isw3000c01v2Entry 103 }

		-- 1.3.6.1.4.1.10106.3.101291.1.1.105
		isw3000c01v2Str1FecEna OBJECT-TYPE
			SYNTAX Bit0No1Yes
			MAX-ACCESS read-write
			STATUS current
			DESCRIPTION
				"Enable FEC"
		::= { isw3000c01v2Entry 105 }

		-- 1.3.6.1.4.1.10106.3.101291.1.1.107
		isw3000c01v2Str1MulticEna OBJECT-TYPE
			SYNTAX IpaTxMode
			MAX-ACCESS read-write
			STATUS current
			DESCRIPTION
				"RX mode"
		::= { isw3000c01v2Entry 107 }

		-- 1.3.6.1.4.1.10106.3.101291.1.1.109
		isw3000c01v2VlanRx1Enable OBJECT-TYPE
			SYNTAX Bit0No1Yes
			MAX-ACCESS read-write
			STATUS current
			DESCRIPTION
				"VLAN Enable"
		::= { isw3000c01v2Entry 109 }

		-- 1.3.6.1.4.1.10106.3.101291.1.1.111
		isw3000c01v2VlanRx1Reg1 OBJECT-TYPE
			SYNTAX Uint8
			MAX-ACCESS read-write
			STATUS current
			DESCRIPTION
				"VLAN_REG_1"
		::= { isw3000c01v2Entry 111 }

		-- 1.3.6.1.4.1.10106.3.101291.1.1.113
		isw3000c01v2VlanRx1Reg2 OBJECT-TYPE
			SYNTAX Uint8
			MAX-ACCESS read-write
			STATUS current
			DESCRIPTION
				"VLAN_REG_2"
		::= { isw3000c01v2Entry 113 }

		-- 1.3.6.1.4.1.10106.3.101291.1.1.115
		isw3000c01v2Str2UipDAdd3 OBJECT-TYPE
			SYNTAX Uint8
			MAX-ACCESS read-write
			STATUS current
			DESCRIPTION
				"Unicast IP address (3)"
		::= { isw3000c01v2Entry 115 }

		-- 1.3.6.1.4.1.10106.3.101291.1.1.117
		isw3000c01v2Str2UipDAdd2 OBJECT-TYPE
			SYNTAX Uint8
			MAX-ACCESS read-write
			STATUS current
			DESCRIPTION
				"Unicast IP address (2)"
		::= { isw3000c01v2Entry 117 }

		-- 1.3.6.1.4.1.10106.3.101291.1.1.119
		isw3000c01v2Str2UipDAdd1 OBJECT-TYPE
			SYNTAX Uint8
			MAX-ACCESS read-write
			STATUS current
			DESCRIPTION
				"Unicast IP address (1)"
		::= { isw3000c01v2Entry 119 }

		-- 1.3.6.1.4.1.10106.3.101291.1.1.121
		isw3000c01v2Str2UipDAdd0 OBJECT-TYPE
			SYNTAX Uint8
			MAX-ACCESS read-write
			STATUS current
			DESCRIPTION
				"Unicast IP address (0)"
		::= { isw3000c01v2Entry 121 }

		-- 1.3.6.1.4.1.10106.3.101291.1.1.123
		isw3000c01v2Str2MipDAdd3 OBJECT-TYPE
			SYNTAX Uint8
			MAX-ACCESS read-write
			STATUS current
			DESCRIPTION
				"Multicast IP address (3)"
		::= { isw3000c01v2Entry 123 }

		-- 1.3.6.1.4.1.10106.3.101291.1.1.125
		isw3000c01v2Str2MipDAdd2 OBJECT-TYPE
			SYNTAX Uint8
			MAX-ACCESS read-write
			STATUS current
			DESCRIPTION
				"Multicast IP address (2)"
		::= { isw3000c01v2Entry 125 }

		-- 1.3.6.1.4.1.10106.3.101291.1.1.127
		isw3000c01v2Str2MipDAdd1 OBJECT-TYPE
			SYNTAX Uint8
			MAX-ACCESS read-write
			STATUS current
			DESCRIPTION
				"Multicast IP address (1)"
		::= { isw3000c01v2Entry 127 }

		-- 1.3.6.1.4.1.10106.3.101291.1.1.129
		isw3000c01v2Str2MipDAdd0 OBJECT-TYPE
			SYNTAX Uint8
			MAX-ACCESS read-write
			STATUS current
			DESCRIPTION
				"Multicast IP address (0)"
		::= { isw3000c01v2Entry 129 }

		-- 1.3.6.1.4.1.10106.3.101291.1.1.131
		isw3000c01v2Str2DPortMsb OBJECT-TYPE
			SYNTAX Uint8
			MAX-ACCESS read-write
			STATUS current
			DESCRIPTION
				"Destination port (msb)"
		::= { isw3000c01v2Entry 131 }

		-- 1.3.6.1.4.1.10106.3.101291.1.1.133
		isw3000c01v2Str2DPortLsb OBJECT-TYPE
			SYNTAX Uint8
			MAX-ACCESS read-write
			STATUS current
			DESCRIPTION
				"Destination port (lsb)"
		::= { isw3000c01v2Entry 133 }

		-- 1.3.6.1.4.1.10106.3.101291.1.1.135
		isw3000c01v2Str2FecEna OBJECT-TYPE
			SYNTAX Bit0No1Yes
			MAX-ACCESS read-write
			STATUS current
			DESCRIPTION
				"Enable FEC"
		::= { isw3000c01v2Entry 135 }

		-- 1.3.6.1.4.1.10106.3.101291.1.1.137
		isw3000c01v2Str2MulticEna OBJECT-TYPE
			SYNTAX IpaTxMode
			MAX-ACCESS read-write
			STATUS current
			DESCRIPTION
				"RX mode"
		::= { isw3000c01v2Entry 137 }

		-- 1.3.6.1.4.1.10106.3.101291.1.1.139
		isw3000c01v2VlanRx2Enable OBJECT-TYPE
			SYNTAX Bit0No1Yes
			MAX-ACCESS read-write
			STATUS current
			DESCRIPTION
				"VLAN Enable"
		::= { isw3000c01v2Entry 139 }

		-- 1.3.6.1.4.1.10106.3.101291.1.1.141
		isw3000c01v2VlanRx2Reg1 OBJECT-TYPE
			SYNTAX Uint8
			MAX-ACCESS read-write
			STATUS current
			DESCRIPTION
				"VLAN_REG_1"
		::= { isw3000c01v2Entry 141 }

		-- 1.3.6.1.4.1.10106.3.101291.1.1.143
		isw3000c01v2VlanRx2Reg2 OBJECT-TYPE
			SYNTAX Uint8
			MAX-ACCESS read-write
			STATUS current
			DESCRIPTION
				"VLAN_REG_2"
		::= { isw3000c01v2Entry 143 }

		-- 1.3.6.1.4.1.10106.3.101291.1.1.145
		isw3000c01v2TxUniEna OBJECT-TYPE
			SYNTAX Bit0No1Yes
			MAX-ACCESS read-write
			STATUS current
			DESCRIPTION
				"Enable TX"
		::= { isw3000c01v2Entry 145 }

		-- 1.3.6.1.4.1.10106.3.101291.1.1.147
		isw3000c01v2TxMultiEna OBJECT-TYPE
			SYNTAX IpaTxMode
			MAX-ACCESS read-write
			STATUS current
			DESCRIPTION
				"TX mode"
		::= { isw3000c01v2Entry 147 }

		-- 1.3.6.1.4.1.10106.3.101291.1.1.149
		isw3000c01v2LocalIpAdd3 OBJECT-TYPE
			SYNTAX Uint8
			MAX-ACCESS read-write
			STATUS current
			DESCRIPTION
				"Unicast IP address (3)"
		::= { isw3000c01v2Entry 149 }

		-- 1.3.6.1.4.1.10106.3.101291.1.1.151
		isw3000c01v2LocalIpAdd2 OBJECT-TYPE
			SYNTAX Uint8
			MAX-ACCESS read-write
			STATUS current
			DESCRIPTION
				"Unicast IP address (2)"
		::= { isw3000c01v2Entry 151 }

		-- 1.3.6.1.4.1.10106.3.101291.1.1.153
		isw3000c01v2LocalIpAdd1 OBJECT-TYPE
			SYNTAX Uint8
			MAX-ACCESS read-write
			STATUS current
			DESCRIPTION
				"Unicast IP address (1)"
		::= { isw3000c01v2Entry 153 }

		-- 1.3.6.1.4.1.10106.3.101291.1.1.155
		isw3000c01v2LocalIpAdd0 OBJECT-TYPE
			SYNTAX Uint8
			MAX-ACCESS read-write
			STATUS current
			DESCRIPTION
				"Unicast IP address (0)"
		::= { isw3000c01v2Entry 155 }

		-- 1.3.6.1.4.1.10106.3.101291.1.1.157
		isw3000c01v2LocalIpMask3 OBJECT-TYPE
			SYNTAX Uint8
			MAX-ACCESS read-write
			STATUS current
			DESCRIPTION
				"IP mask (3)"
		::= { isw3000c01v2Entry 157 }

		-- 1.3.6.1.4.1.10106.3.101291.1.1.159
		isw3000c01v2LocalIpMask2 OBJECT-TYPE
			SYNTAX Uint8
			MAX-ACCESS read-write
			STATUS current
			DESCRIPTION
				"IP mask (2)"
		::= { isw3000c01v2Entry 159 }

		-- 1.3.6.1.4.1.10106.3.101291.1.1.161
		isw3000c01v2LocalIpMask1 OBJECT-TYPE
			SYNTAX Uint8
			MAX-ACCESS read-write
			STATUS current
			DESCRIPTION
				"IP mask (1)"
		::= { isw3000c01v2Entry 161 }

		-- 1.3.6.1.4.1.10106.3.101291.1.1.163
		isw3000c01v2LocalIpMask0 OBJECT-TYPE
			SYNTAX Uint8
			MAX-ACCESS read-write
			STATUS current
			DESCRIPTION
				"IP mask (0)"
		::= { isw3000c01v2Entry 163 }

		-- 1.3.6.1.4.1.10106.3.101291.1.1.165
		isw3000c01v2LocalIpGway3 OBJECT-TYPE
			SYNTAX Uint8
			MAX-ACCESS read-write
			STATUS current
			DESCRIPTION
				"Gateway IP address (3)"
		::= { isw3000c01v2Entry 165 }

		-- 1.3.6.1.4.1.10106.3.101291.1.1.167
		isw3000c01v2LocalIpGway2 OBJECT-TYPE
			SYNTAX Uint8
			MAX-ACCESS read-write
			STATUS current
			DESCRIPTION
				"Gateway IP address (2)"
		::= { isw3000c01v2Entry 167 }

		-- 1.3.6.1.4.1.10106.3.101291.1.1.169
		isw3000c01v2LocalIpGway1 OBJECT-TYPE
			SYNTAX Uint8
			MAX-ACCESS read-write
			STATUS current
			DESCRIPTION
				"Gateway IP address (1)"
		::= { isw3000c01v2Entry 169 }

		-- 1.3.6.1.4.1.10106.3.101291.1.1.171
		isw3000c01v2LocalIpGway0 OBJECT-TYPE
			SYNTAX Uint8
			MAX-ACCESS read-write
			STATUS current
			DESCRIPTION
				"Gateway IP address (0)"
		::= { isw3000c01v2Entry 171 }

		-- 1.3.6.1.4.1.10106.3.101291.1.1.173
		isw3000c01v2TxUipAdd3 OBJECT-TYPE
			SYNTAX Uint8
			MAX-ACCESS read-write
			STATUS current
			DESCRIPTION
				"Destination IP address (3)"
		::= { isw3000c01v2Entry 173 }

		-- 1.3.6.1.4.1.10106.3.101291.1.1.175
		isw3000c01v2TxUipAdd2 OBJECT-TYPE
			SYNTAX Uint8
			MAX-ACCESS read-write
			STATUS current
			DESCRIPTION
				"Destination IP address (2)"
		::= { isw3000c01v2Entry 175 }

		-- 1.3.6.1.4.1.10106.3.101291.1.1.177
		isw3000c01v2TxUipAdd1 OBJECT-TYPE
			SYNTAX Uint8
			MAX-ACCESS read-write
			STATUS current
			DESCRIPTION
				"Destination IP address (1)"
		::= { isw3000c01v2Entry 177 }

		-- 1.3.6.1.4.1.10106.3.101291.1.1.179
		isw3000c01v2TxUipAdd0 OBJECT-TYPE
			SYNTAX Uint8
			MAX-ACCESS read-write
			STATUS current
			DESCRIPTION
				"Destination IP address (0)"
		::= { isw3000c01v2Entry 179 }

		-- 1.3.6.1.4.1.10106.3.101291.1.1.181
		isw3000c01v2TxMipAdd3 OBJECT-TYPE
			SYNTAX Uint8
			MAX-ACCESS read-write
			STATUS current
			DESCRIPTION
				"Multicast dest. IP address (3)"
		::= { isw3000c01v2Entry 181 }

		-- 1.3.6.1.4.1.10106.3.101291.1.1.183
		isw3000c01v2TxMipAdd2 OBJECT-TYPE
			SYNTAX Uint8
			MAX-ACCESS read-write
			STATUS current
			DESCRIPTION
				"Multicast dest. IP address (2)"
		::= { isw3000c01v2Entry 183 }

		-- 1.3.6.1.4.1.10106.3.101291.1.1.185
		isw3000c01v2TxMipAdd1 OBJECT-TYPE
			SYNTAX Uint8
			MAX-ACCESS read-write
			STATUS current
			DESCRIPTION
				"Multicast dest. IP address (1)"
		::= { isw3000c01v2Entry 185 }

		-- 1.3.6.1.4.1.10106.3.101291.1.1.187
		isw3000c01v2TxMipAdd0 OBJECT-TYPE
			SYNTAX Uint8
			MAX-ACCESS read-write
			STATUS current
			DESCRIPTION
				"Multicast dest. IP address (0)"
		::= { isw3000c01v2Entry 187 }

		-- 1.3.6.1.4.1.10106.3.101291.1.1.189
		isw3000c01v2TxSPortMsb OBJECT-TYPE
			SYNTAX Uint8
			MAX-ACCESS read-write
			STATUS current
			DESCRIPTION
				"Source port (msb)"
		::= { isw3000c01v2Entry 189 }

		-- 1.3.6.1.4.1.10106.3.101291.1.1.191
		isw3000c01v2TxSPortLsb OBJECT-TYPE
			SYNTAX Uint8
			MAX-ACCESS read-write
			STATUS current
			DESCRIPTION
				"Source port (lsb)"
		::= { isw3000c01v2Entry 191 }

		-- 1.3.6.1.4.1.10106.3.101291.1.1.193
		isw3000c01v2TxDPortMsb OBJECT-TYPE
			SYNTAX Uint8
			MAX-ACCESS read-write
			STATUS current
			DESCRIPTION
				"Destination port (msb)"
		::= { isw3000c01v2Entry 193 }

		-- 1.3.6.1.4.1.10106.3.101291.1.1.195
		isw3000c01v2TxDPortLsb OBJECT-TYPE
			SYNTAX Uint8
			MAX-ACCESS read-write
			STATUS current
			DESCRIPTION
				"Destination port (lsb)"
		::= { isw3000c01v2Entry 195 }

		-- 1.3.6.1.4.1.10106.3.101291.1.1.197
		isw3000c01v2VlanTxEnable OBJECT-TYPE
			SYNTAX Bit0No1Yes
			MAX-ACCESS read-write
			STATUS current
			DESCRIPTION
				"VLAN Enable"
		::= { isw3000c01v2Entry 197 }

		-- 1.3.6.1.4.1.10106.3.101291.1.1.199
		isw3000c01v2VlanTxPriority OBJECT-TYPE
			SYNTAX Uint3
			MAX-ACCESS read-write
			STATUS current
			DESCRIPTION
				"VLAN Priority"
		::= { isw3000c01v2Entry 199 }

		-- 1.3.6.1.4.1.10106.3.101291.1.1.201
		isw3000c01v2VlanTxReg1 OBJECT-TYPE
			SYNTAX Uint8
			MAX-ACCESS read-write
			STATUS current
			DESCRIPTION
				"VLAN_REG_1"
		::= { isw3000c01v2Entry 201 }

		-- 1.3.6.1.4.1.10106.3.101291.1.1.203
		isw3000c01v2VlanTxReg2 OBJECT-TYPE
			SYNTAX Uint8
			MAX-ACCESS read-write
			STATUS current
			DESCRIPTION
				"VLAN_REG_2"
		::= { isw3000c01v2Entry 203 }

		-- 1.3.6.1.4.1.10106.3.101291.1.1.205
		isw3000c01v2TxLParam OBJECT-TYPE
			SYNTAX Uint5
			MAX-ACCESS read-write
			STATUS current
			DESCRIPTION
				"L parameter (FEC mode columns)"
		::= { isw3000c01v2Entry 205 }

		-- 1.3.6.1.4.1.10106.3.101291.1.1.207
		isw3000c01v2TxFecMode OBJECT-TYPE
			SYNTAX FecMode
			MAX-ACCESS read-write
			STATUS current
			DESCRIPTION
				"Protocol"
		::= { isw3000c01v2Entry 207 }

		-- 1.3.6.1.4.1.10106.3.101291.1.1.209
		isw3000c01v2TxDParam OBJECT-TYPE
			SYNTAX Uint5
			MAX-ACCESS read-write
			STATUS current
			DESCRIPTION
				"D parameter (FEC mode rows)"
		::= { isw3000c01v2Entry 209 }

		-- 1.3.6.1.4.1.10106.3.101291.1.1.211
		isw3000c01v2TxTspkInIppk OBJECT-TYPE
			SYNTAX Uint3
			MAX-ACCESS read-write
			STATUS current
			DESCRIPTION
				"TS packets in each IP packet"
		::= { isw3000c01v2Entry 211 }

		-- 1.3.6.1.4.1.10106.3.101291.1.1.213
		isw3000c01v2TxRowDelay OBJECT-TYPE
			SYNTAX Uint5
			MAX-ACCESS read-write
			STATUS current
			DESCRIPTION
				"FEC row delay"
		::= { isw3000c01v2Entry 213 }

		-- 1.3.6.1.4.1.10106.3.101291.1.1.215
		isw3000c01v2TxColDelay OBJECT-TYPE
			SYNTAX Uint8
			MAX-ACCESS read-write
			STATUS current
			DESCRIPTION
				"FEC column delay"
		::= { isw3000c01v2Entry 215 }

		-- 1.3.6.1.4.1.10106.3.101291.1.1.217
		isw3000c01v2LowCost OBJECT-TYPE
			SYNTAX Bit0No1Yes
			MAX-ACCESS read-write
			STATUS current
			DESCRIPTION
				"TOS.  Low cost"
		::= { isw3000c01v2Entry 217 }

		-- 1.3.6.1.4.1.10106.3.101291.1.1.219
		isw3000c01v2HighReliabilty OBJECT-TYPE
			SYNTAX Bit0No1Yes
			MAX-ACCESS read-write
			STATUS current
			DESCRIPTION
				"TOS. High reliability"
		::= { isw3000c01v2Entry 219 }

		-- 1.3.6.1.4.1.10106.3.101291.1.1.221
		isw3000c01v2HighThroughput OBJECT-TYPE
			SYNTAX Bit0No1Yes
			MAX-ACCESS read-write
			STATUS current
			DESCRIPTION
				"TOS. High Throughput"
		::= { isw3000c01v2Entry 221 }

		-- 1.3.6.1.4.1.10106.3.101291.1.1.223
		isw3000c01v2LowDelay OBJECT-TYPE
			SYNTAX Bit0No1Yes
			MAX-ACCESS read-write
			STATUS current
			DESCRIPTION
				"TOS. Low delay"
		::= { isw3000c01v2Entry 223 }

		-- 1.3.6.1.4.1.10106.3.101291.1.1.225
		isw3000c01v2Precedence OBJECT-TYPE
			SYNTAX IpaPrecedence
			MAX-ACCESS read-write
			STATUS current
			DESCRIPTION
				"TOS. Precedence"
		::= { isw3000c01v2Entry 225 }

		-- 1.3.6.1.4.1.10106.3.101291.1.1.227
		isw3000c01v2Ttl OBJECT-TYPE
			SYNTAX Uint8
			MAX-ACCESS read-write
			STATUS current
			DESCRIPTION
				"Time to live"
		::= { isw3000c01v2Entry 227 }

		-- 1.3.6.1.4.1.10106.3.101291.1.1.229
		isw3000c01v2Str1IgmFAdd3 OBJECT-TYPE
			SYNTAX Uint8
			MAX-ACCESS read-write
			STATUS current
			DESCRIPTION
				"Source IP address (3)"
		::= { isw3000c01v2Entry 229 }

		-- 1.3.6.1.4.1.10106.3.101291.1.1.231
		isw3000c01v2Str1IgmFAdd2 OBJECT-TYPE
			SYNTAX Uint8
			MAX-ACCESS read-write
			STATUS current
			DESCRIPTION
				"Source IP address (2)"
		::= { isw3000c01v2Entry 231 }

		-- 1.3.6.1.4.1.10106.3.101291.1.1.233
		isw3000c01v2Str1IgmFAdd1 OBJECT-TYPE
			SYNTAX Uint8
			MAX-ACCESS read-write
			STATUS current
			DESCRIPTION
				"Source IP address (1)"
		::= { isw3000c01v2Entry 233 }

		-- 1.3.6.1.4.1.10106.3.101291.1.1.235
		isw3000c01v2Str1IgmFAdd0 OBJECT-TYPE
			SYNTAX Uint8
			MAX-ACCESS read-write
			STATUS current
			DESCRIPTION
				"Source IP address (0)"
		::= { isw3000c01v2Entry 235 }

		-- 1.3.6.1.4.1.10106.3.101291.1.1.237
		isw3000c01v2Str2IgmFAdd3 OBJECT-TYPE
			SYNTAX Uint8
			MAX-ACCESS read-write
			STATUS current
			DESCRIPTION
				"Source IP address (3)"
		::= { isw3000c01v2Entry 237 }

		-- 1.3.6.1.4.1.10106.3.101291.1.1.239
		isw3000c01v2Str2IgmFAdd2 OBJECT-TYPE
			SYNTAX Uint8
			MAX-ACCESS read-write
			STATUS current
			DESCRIPTION
				"Source IP address (2)"
		::= { isw3000c01v2Entry 239 }

		-- 1.3.6.1.4.1.10106.3.101291.1.1.241
		isw3000c01v2Str2IgmFAdd1 OBJECT-TYPE
			SYNTAX Uint8
			MAX-ACCESS read-write
			STATUS current
			DESCRIPTION
				"Source IP address (1)"
		::= { isw3000c01v2Entry 241 }

		-- 1.3.6.1.4.1.10106.3.101291.1.1.243
		isw3000c01v2Str2IgmFAdd0 OBJECT-TYPE
			SYNTAX Uint8
			MAX-ACCESS read-write
			STATUS current
			DESCRIPTION
				"Source IP address (0)"
		::= { isw3000c01v2Entry 243 }

		-- 1.3.6.1.4.1.10106.3.101291.1.1.245
		isw3000c01v2MaxBitrateNull OBJECT-TYPE
			SYNTAX Bitrate
			MAX-ACCESS read-write
			STATUS current
			DESCRIPTION
				"Upper bitrate limit"
		::= { isw3000c01v2Entry 245 }

		-- 1.3.6.1.4.1.10106.3.101291.1.1.247
		isw3000c01v2MinBitrateNull OBJECT-TYPE
			SYNTAX Bitrate
			MAX-ACCESS read-write
			STATUS current
			DESCRIPTION
				"Lower bitrate limit"
		::= { isw3000c01v2Entry 247 }

		-- 1.3.6.1.4.1.10106.3.101291.1.1.249
		isw3000c01v2PckNullMax OBJECT-TYPE
			SYNTAX PckNullRate1
			MAX-ACCESS read-write
			STATUS current
			DESCRIPTION
				"Upper packet null ratio limit"
		::= { isw3000c01v2Entry 249 }

		-- 1.3.6.1.4.1.10106.3.101291.1.1.251
		isw3000c01v2PckNullMin OBJECT-TYPE
			SYNTAX PckNullRate1
			MAX-ACCESS read-write
			STATUS current
			DESCRIPTION
				"Lower packet null ratio limit"
		::= { isw3000c01v2Entry 251 }

		-- 1.3.6.1.4.1.10106.3.101291.1.1.253
		isw3000c01v2DvbT2Lock1 OBJECT-TYPE
			SYNTAX DvbT2Locked
			MAX-ACCESS read-only
			STATUS current
			DESCRIPTION
				"DVB-T2 locked"
		::= { isw3000c01v2Entry 253 }

		-- 1.3.6.1.4.1.10106.3.101291.1.1.254
		isw3000c01v2DvbT2Lock1TrapEnable OBJECT-TYPE
			SYNTAX AlarmEnable
			MAX-ACCESS read-write
			STATUS current
			DESCRIPTION
				"DVB-T2 locked Trap Enable"
		::= { isw3000c01v2Entry 254 }

		-- 1.3.6.1.4.1.10106.3.101291.1.1.255
		isw3000c01v2DvbT2Lock2 OBJECT-TYPE
			SYNTAX DvbT2Locked
			MAX-ACCESS read-only
			STATUS current
			DESCRIPTION
				"DVB-T2 locked"
		::= { isw3000c01v2Entry 255 }

		-- 1.3.6.1.4.1.10106.3.101291.1.1.256
		isw3000c01v2DvbT2Lock2TrapEnable OBJECT-TYPE
			SYNTAX AlarmEnable
			MAX-ACCESS read-write
			STATUS current
			DESCRIPTION
				"DVB-T2 locked Trap Enable"
		::= { isw3000c01v2Entry 256 }

		-- 1.3.6.1.4.1.10106.3.101291.1.1.257
		isw3000c01v2Ts1DelayExt OBJECT-TYPE
			SYNTAX DelayX02Ms
			MAX-ACCESS read-only
			STATUS current
			DESCRIPTION
				"DVB-T mode: input delay refered to 1PPS reference"
		::= { isw3000c01v2Entry 257 }

		-- 1.3.6.1.4.1.10106.3.101291.1.1.259
		isw3000c01v2Ts2DelayExt OBJECT-TYPE
			SYNTAX DelayX02Ms
			MAX-ACCESS read-only
			STATUS current
			DESCRIPTION
				"DVB-T mode: input delay refered to 1PPS reference"
		::= { isw3000c01v2Entry 259 }

		-- 1.3.6.1.4.1.10106.3.101291.1.1.261
		isw3000c01v2DelayT20S OBJECT-TYPE
			SYNTAX DelayX1S
			MAX-ACCESS read-only
			STATUS current
			DESCRIPTION
				"Seconds in advance (DVB-T2 absolute mode only)"
		::= { isw3000c01v2Entry 261 }

		-- 1.3.6.1.4.1.10106.3.101291.1.1.263
		isw3000c01v2DelayT20Ms OBJECT-TYPE
			SYNTAX DelayX100Ns
			MAX-ACCESS read-only
			STATUS current
			DESCRIPTION
				"Time in advance in ns (DVB-T2 mode)"
		::= { isw3000c01v2Entry 263 }

		-- 1.3.6.1.4.1.10106.3.101291.1.1.265
		isw3000c01v2DelayT21S OBJECT-TYPE
			SYNTAX DelayX1S
			MAX-ACCESS read-only
			STATUS current
			DESCRIPTION
				"Seconds in advance (DVB-T2 absolute mode only)"
		::= { isw3000c01v2Entry 265 }

		-- 1.3.6.1.4.1.10106.3.101291.1.1.267
		isw3000c01v2DelayT21Ms OBJECT-TYPE
			SYNTAX DelayX100Ns
			MAX-ACCESS read-only
			STATUS current
			DESCRIPTION
				"Time in advance in ns (DVB-T2 mode)"
		::= { isw3000c01v2Entry 267 }

		-- 1.3.6.1.4.1.10106.3.101291.1.1.269
		isw3000c01v2Bitrate1 OBJECT-TYPE
			SYNTAX Bitrate
			MAX-ACCESS read-only
			STATUS current
			DESCRIPTION
				"Bitrate"
		::= { isw3000c01v2Entry 269 }

		-- 1.3.6.1.4.1.10106.3.101291.1.1.271
		isw3000c01v2Bitrate2 OBJECT-TYPE
			SYNTAX Bitrate
			MAX-ACCESS read-only
			STATUS current
			DESCRIPTION
				"Bitrate"
		::= { isw3000c01v2Entry 271 }

		-- 1.3.6.1.4.1.10106.3.101291.1.1.273
		isw3000c01v2BitrateNull1 OBJECT-TYPE
			SYNTAX Bitrate
			MAX-ACCESS read-only
			STATUS current
			DESCRIPTION
				"Bitrate null packets"
		::= { isw3000c01v2Entry 273 }

		-- 1.3.6.1.4.1.10106.3.101291.1.1.275
		isw3000c01v2BitrateNull2 OBJECT-TYPE
			SYNTAX Bitrate
			MAX-ACCESS read-only
			STATUS current
			DESCRIPTION
				"Bitrate null packets"
		::= { isw3000c01v2Entry 275 }

		-- 1.3.6.1.4.1.10106.3.101291.1.1.277
		isw3000c01v2Ts1PckNull OBJECT-TYPE
			SYNTAX PckNullRate1
			MAX-ACCESS read-only
			STATUS current
			DESCRIPTION
				"Packet null ratio"
		::= { isw3000c01v2Entry 277 }

		-- 1.3.6.1.4.1.10106.3.101291.1.1.279
		isw3000c01v2Ts2PckNull OBJECT-TYPE
			SYNTAX PckNullRate1
			MAX-ACCESS read-only
			STATUS current
			DESCRIPTION
				"Packet null ratio"
		::= { isw3000c01v2Entry 279 }

		-- 1.3.6.1.4.1.10106.3.101291.1.1.281
		isw3000c01v2Ts1TraffFail OBJECT-TYPE
			SYNTAX BitFail
			MAX-ACCESS read-only
			STATUS current
			DESCRIPTION
				"Bitrate status"
		::= { isw3000c01v2Entry 281 }

		-- 1.3.6.1.4.1.10106.3.101291.1.1.282
		isw3000c01v2Ts1TraffFailTrapEnable OBJECT-TYPE
			SYNTAX AlarmEnable
			MAX-ACCESS read-write
			STATUS current
			DESCRIPTION
				"Bitrate status Trap Enable"
		::= { isw3000c01v2Entry 282 }

		-- 1.3.6.1.4.1.10106.3.101291.1.1.283
		isw3000c01v2Ts1NullPFail OBJECT-TYPE
			SYNTAX BitFail
			MAX-ACCESS read-only
			STATUS current
			DESCRIPTION
				"Null packet rate status"
		::= { isw3000c01v2Entry 283 }

		-- 1.3.6.1.4.1.10106.3.101291.1.1.284
		isw3000c01v2Ts1NullPFailTrapEnable OBJECT-TYPE
			SYNTAX AlarmEnable
			MAX-ACCESS read-write
			STATUS current
			DESCRIPTION
				"Null packet rate status Trap Enable"
		::= { isw3000c01v2Entry 284 }

		-- 1.3.6.1.4.1.10106.3.101291.1.1.285
		isw3000c01v2Ts2TraffFail OBJECT-TYPE
			SYNTAX BitFail
			MAX-ACCESS read-only
			STATUS current
			DESCRIPTION
				"Bitrate status"
		::= { isw3000c01v2Entry 285 }

		-- 1.3.6.1.4.1.10106.3.101291.1.1.286
		isw3000c01v2Ts2TraffFailTrapEnable OBJECT-TYPE
			SYNTAX AlarmEnable
			MAX-ACCESS read-write
			STATUS current
			DESCRIPTION
				"Bitrate status Trap Enable"
		::= { isw3000c01v2Entry 286 }

		-- 1.3.6.1.4.1.10106.3.101291.1.1.287
		isw3000c01v2Ts2NullPFail OBJECT-TYPE
			SYNTAX BitFail
			MAX-ACCESS read-only
			STATUS current
			DESCRIPTION
				"Null packet rate status"
		::= { isw3000c01v2Entry 287 }

		-- 1.3.6.1.4.1.10106.3.101291.1.1.288
		isw3000c01v2Ts2NullPFailTrapEnable OBJECT-TYPE
			SYNTAX AlarmEnable
			MAX-ACCESS read-write
			STATUS current
			DESCRIPTION
				"Null packet rate status Trap Enable"
		::= { isw3000c01v2Entry 288 }

		-- 1.3.6.1.4.1.10106.3.101291.1.1.289
		isw3000c01v21ppsFail OBJECT-TYPE
			SYNTAX BitFail
			MAX-ACCESS read-only
			STATUS current
			DESCRIPTION
				"1PPS reference input status"
		::= { isw3000c01v2Entry 289 }

		-- 1.3.6.1.4.1.10106.3.101291.1.1.290
		isw3000c01v21ppsFailTrapEnable OBJECT-TYPE
			SYNTAX AlarmEnable
			MAX-ACCESS read-write
			STATUS current
			DESCRIPTION
				"1PPS reference input status Trap Enable"
		::= { isw3000c01v2Entry 290 }

		-- 1.3.6.1.4.1.10106.3.101291.1.1.291
		isw3000c01v210mhzFail OBJECT-TYPE
			SYNTAX BitFail
			MAX-ACCESS read-only
			STATUS current
			DESCRIPTION
				"10MHz reference input status"
		::= { isw3000c01v2Entry 291 }

		-- 1.3.6.1.4.1.10106.3.101291.1.1.292
		isw3000c01v210mhzFailTrapEnable OBJECT-TYPE
			SYNTAX AlarmEnable
			MAX-ACCESS read-write
			STATUS current
			DESCRIPTION
				"10MHz reference input status Trap Enable"
		::= { isw3000c01v2Entry 292 }

		-- 1.3.6.1.4.1.10106.3.101291.1.1.293
		isw3000c01v2OutputFail OBJECT-TYPE
			SYNTAX BitFail
			MAX-ACCESS read-only
			STATUS current
			DESCRIPTION
				"The output signal is not valid because all inputs failed"
		::= { isw3000c01v2Entry 293 }

		-- 1.3.6.1.4.1.10106.3.101291.1.1.294
		isw3000c01v2OutputFailTrapEnable OBJECT-TYPE
			SYNTAX AlarmEnable
			MAX-ACCESS read-write
			STATUS current
			DESCRIPTION
				"The output signal is not valid because all inputs failed Trap Enable"
		::= { isw3000c01v2Entry 294 }

		-- 1.3.6.1.4.1.10106.3.101291.1.1.295
		isw3000c01v2Ts1DelWar OBJECT-TYPE
			SYNTAX BitFail
			MAX-ACCESS read-only
			STATUS current
			DESCRIPTION
				"The delay is greater than the programmed output delay"
		::= { isw3000c01v2Entry 295 }

		-- 1.3.6.1.4.1.10106.3.101291.1.1.296
		isw3000c01v2Ts1DelWarTrapEnable OBJECT-TYPE
			SYNTAX AlarmEnable
			MAX-ACCESS read-write
			STATUS current
			DESCRIPTION
				"The delay is greater than the programmed output delay Trap Enable"
		::= { isw3000c01v2Entry 296 }

		-- 1.3.6.1.4.1.10106.3.101291.1.1.297
		isw3000c01v2Ts2DelWar OBJECT-TYPE
			SYNTAX BitFail
			MAX-ACCESS read-only
			STATUS current
			DESCRIPTION
				"The delay is greater than the programmed output delay"
		::= { isw3000c01v2Entry 297 }

		-- 1.3.6.1.4.1.10106.3.101291.1.1.298
		isw3000c01v2Ts2DelWarTrapEnable OBJECT-TYPE
			SYNTAX AlarmEnable
			MAX-ACCESS read-write
			STATUS current
			DESCRIPTION
				"The delay is greater than the programmed output delay Trap Enable"
		::= { isw3000c01v2Entry 298 }

		-- 1.3.6.1.4.1.10106.3.101291.1.1.299
		isw3000c01v2ExtFail1 OBJECT-TYPE
			SYNTAX BitFail
			MAX-ACCESS read-only
			STATUS current
			DESCRIPTION
				"External input fail status"
		::= { isw3000c01v2Entry 299 }

		-- 1.3.6.1.4.1.10106.3.101291.1.1.300
		isw3000c01v2ExtFail1TrapEnable OBJECT-TYPE
			SYNTAX AlarmEnable
			MAX-ACCESS read-write
			STATUS current
			DESCRIPTION
				"External input fail status Trap Enable"
		::= { isw3000c01v2Entry 300 }

		-- 1.3.6.1.4.1.10106.3.101291.1.1.301
		isw3000c01v2ExtFail2 OBJECT-TYPE
			SYNTAX BitFail
			MAX-ACCESS read-only
			STATUS current
			DESCRIPTION
				"External input fail status"
		::= { isw3000c01v2Entry 301 }

		-- 1.3.6.1.4.1.10106.3.101291.1.1.302
		isw3000c01v2ExtFail2TrapEnable OBJECT-TYPE
			SYNTAX AlarmEnable
			MAX-ACCESS read-write
			STATUS current
			DESCRIPTION
				"External input fail status Trap Enable"
		::= { isw3000c01v2Entry 302 }

		-- 1.3.6.1.4.1.10106.3.101291.1.1.303
		isw3000c01v2GlobalSeam OBJECT-TYPE
			SYNTAX Bit0Sea1Nse
			MAX-ACCESS read-only
			STATUS current
			DESCRIPTION
				"Global seamles switching capability"
		::= { isw3000c01v2Entry 303 }

		-- 1.3.6.1.4.1.10106.3.101291.1.1.304
		isw3000c01v2GlobalSeamTrapEnable OBJECT-TYPE
			SYNTAX AlarmEnable
			MAX-ACCESS read-write
			STATUS current
			DESCRIPTION
				"Global seamles switching capability Trap Enable"
		::= { isw3000c01v2Entry 304 }

		-- 1.3.6.1.4.1.10106.3.101291.1.1.305
		isw3000c01v2SyncLossErr1 OBJECT-TYPE
			SYNTAX BitFail
			MAX-ACCESS read-only
			STATUS current
			DESCRIPTION
				"Sync loss fail (Fist priority  parameter 1.1)"
		::= { isw3000c01v2Entry 305 }

		-- 1.3.6.1.4.1.10106.3.101291.1.1.306
		isw3000c01v2SyncLossErr1TrapEnable OBJECT-TYPE
			SYNTAX AlarmEnable
			MAX-ACCESS read-write
			STATUS current
			DESCRIPTION
				"Sync loss fail (Fist priority  parameter 1.1) Trap Enable"
		::= { isw3000c01v2Entry 306 }

		-- 1.3.6.1.4.1.10106.3.101291.1.1.307
		isw3000c01v2SyncByteErr1 OBJECT-TYPE
			SYNTAX BitFail
			MAX-ACCESS read-only
			STATUS current
			DESCRIPTION
				"Sync byte error (Fist priority  parameter 1.2)"
		::= { isw3000c01v2Entry 307 }

		-- 1.3.6.1.4.1.10106.3.101291.1.1.308
		isw3000c01v2SyncByteErr1TrapEnable OBJECT-TYPE
			SYNTAX AlarmEnable
			MAX-ACCESS read-write
			STATUS current
			DESCRIPTION
				"Sync byte error (Fist priority  parameter 1.2) Trap Enable"
		::= { isw3000c01v2Entry 308 }

		-- 1.3.6.1.4.1.10106.3.101291.1.1.309
		isw3000c01v2PatError1 OBJECT-TYPE
			SYNTAX BitFail
			MAX-ACCESS read-only
			STATUS current
			DESCRIPTION
				"PAT error (Fist priority  parameter 1.3)"
		::= { isw3000c01v2Entry 309 }

		-- 1.3.6.1.4.1.10106.3.101291.1.1.310
		isw3000c01v2PatError1TrapEnable OBJECT-TYPE
			SYNTAX AlarmEnable
			MAX-ACCESS read-write
			STATUS current
			DESCRIPTION
				"PAT error (Fist priority  parameter 1.3) Trap Enable"
		::= { isw3000c01v2Entry 310 }

		-- 1.3.6.1.4.1.10106.3.101291.1.1.311
		isw3000c01v2CcError1 OBJECT-TYPE
			SYNTAX BitFail
			MAX-ACCESS read-only
			STATUS current
			DESCRIPTION
				"Continuity counter error (Fist priority  parameter 1.4)"
		::= { isw3000c01v2Entry 311 }

		-- 1.3.6.1.4.1.10106.3.101291.1.1.312
		isw3000c01v2CcError1TrapEnable OBJECT-TYPE
			SYNTAX AlarmEnable
			MAX-ACCESS read-write
			STATUS current
			DESCRIPTION
				"Continuity counter error (Fist priority  parameter 1.4) Trap Enable"
		::= { isw3000c01v2Entry 312 }

		-- 1.3.6.1.4.1.10106.3.101291.1.1.313
		isw3000c01v2PmtError1 OBJECT-TYPE
			SYNTAX BitFail
			MAX-ACCESS read-only
			STATUS current
			DESCRIPTION
				"PMT error (Fist priority  parameter 1.5)"
		::= { isw3000c01v2Entry 313 }

		-- 1.3.6.1.4.1.10106.3.101291.1.1.314
		isw3000c01v2PmtError1TrapEnable OBJECT-TYPE
			SYNTAX AlarmEnable
			MAX-ACCESS read-write
			STATUS current
			DESCRIPTION
				"PMT error (Fist priority  parameter 1.5) Trap Enable"
		::= { isw3000c01v2Entry 314 }

		-- 1.3.6.1.4.1.10106.3.101291.1.1.315
		isw3000c01v2PidError1 OBJECT-TYPE
			SYNTAX BitFail
			MAX-ACCESS read-only
			STATUS current
			DESCRIPTION
				"PID error (Fist priority  parameter 1.6)"
		::= { isw3000c01v2Entry 315 }

		-- 1.3.6.1.4.1.10106.3.101291.1.1.316
		isw3000c01v2PidError1TrapEnable OBJECT-TYPE
			SYNTAX AlarmEnable
			MAX-ACCESS read-write
			STATUS current
			DESCRIPTION
				"PID error (Fist priority  parameter 1.6) Trap Enable"
		::= { isw3000c01v2Entry 316 }

		-- 1.3.6.1.4.1.10106.3.101291.1.1.317
		isw3000c01v2MipError1 OBJECT-TYPE
			SYNTAX BitFail
			MAX-ACCESS read-only
			STATUS current
			DESCRIPTION
				"MIP error. DVB-T compliant"
		::= { isw3000c01v2Entry 317 }

		-- 1.3.6.1.4.1.10106.3.101291.1.1.318
		isw3000c01v2MipError1TrapEnable OBJECT-TYPE
			SYNTAX AlarmEnable
			MAX-ACCESS read-write
			STATUS current
			DESCRIPTION
				"MIP error. DVB-T compliant Trap Enable"
		::= { isw3000c01v2Entry 318 }

		-- 1.3.6.1.4.1.10106.3.101291.1.1.319
		isw3000c01v2GlobalError1 OBJECT-TYPE
			SYNTAX BitFail
			MAX-ACCESS read-only
			STATUS current
			DESCRIPTION
				"Global fail"
		::= { isw3000c01v2Entry 319 }

		-- 1.3.6.1.4.1.10106.3.101291.1.1.320
		isw3000c01v2GlobalError1TrapEnable OBJECT-TYPE
			SYNTAX AlarmEnable
			MAX-ACCESS read-write
			STATUS current
			DESCRIPTION
				"Global fail Trap Enable"
		::= { isw3000c01v2Entry 320 }

		-- 1.3.6.1.4.1.10106.3.101291.1.1.321
		isw3000c01v2GlobalError1G OBJECT-TYPE
			SYNTAX BitFail
			MAX-ACCESS read-only
			STATUS current
			DESCRIPTION
				"Global fail TS 1"
		::= { isw3000c01v2Entry 321 }

		-- 1.3.6.1.4.1.10106.3.101291.1.1.323
		isw3000c01v2SyncLossErr2 OBJECT-TYPE
			SYNTAX BitFail
			MAX-ACCESS read-only
			STATUS current
			DESCRIPTION
				"Sync loss fail (Fist priority  parameter 1.1)"
		::= { isw3000c01v2Entry 323 }

		-- 1.3.6.1.4.1.10106.3.101291.1.1.324
		isw3000c01v2SyncLossErr2TrapEnable OBJECT-TYPE
			SYNTAX AlarmEnable
			MAX-ACCESS read-write
			STATUS current
			DESCRIPTION
				"Sync loss fail (Fist priority  parameter 1.1) Trap Enable"
		::= { isw3000c01v2Entry 324 }

		-- 1.3.6.1.4.1.10106.3.101291.1.1.325
		isw3000c01v2SyncByteErr2 OBJECT-TYPE
			SYNTAX BitFail
			MAX-ACCESS read-only
			STATUS current
			DESCRIPTION
				"Sync byte error (Fist priority  parameter 1.2)"
		::= { isw3000c01v2Entry 325 }

		-- 1.3.6.1.4.1.10106.3.101291.1.1.326
		isw3000c01v2SyncByteErr2TrapEnable OBJECT-TYPE
			SYNTAX AlarmEnable
			MAX-ACCESS read-write
			STATUS current
			DESCRIPTION
				"Sync byte error (Fist priority  parameter 1.2) Trap Enable"
		::= { isw3000c01v2Entry 326 }

		-- 1.3.6.1.4.1.10106.3.101291.1.1.327
		isw3000c01v2PatError2 OBJECT-TYPE
			SYNTAX BitFail
			MAX-ACCESS read-only
			STATUS current
			DESCRIPTION
				"PAT error (Fist priority  parameter 1.3)"
		::= { isw3000c01v2Entry 327 }

		-- 1.3.6.1.4.1.10106.3.101291.1.1.328
		isw3000c01v2PatError2TrapEnable OBJECT-TYPE
			SYNTAX AlarmEnable
			MAX-ACCESS read-write
			STATUS current
			DESCRIPTION
				"PAT error (Fist priority  parameter 1.3) Trap Enable"
		::= { isw3000c01v2Entry 328 }

		-- 1.3.6.1.4.1.10106.3.101291.1.1.329
		isw3000c01v2CcError2 OBJECT-TYPE
			SYNTAX BitFail
			MAX-ACCESS read-only
			STATUS current
			DESCRIPTION
				"Continuity counter error (Fist priority  parameter 1.4)"
		::= { isw3000c01v2Entry 329 }

		-- 1.3.6.1.4.1.10106.3.101291.1.1.330
		isw3000c01v2CcError2TrapEnable OBJECT-TYPE
			SYNTAX AlarmEnable
			MAX-ACCESS read-write
			STATUS current
			DESCRIPTION
				"Continuity counter error (Fist priority  parameter 1.4) Trap Enable"
		::= { isw3000c01v2Entry 330 }

		-- 1.3.6.1.4.1.10106.3.101291.1.1.331
		isw3000c01v2PmtError2 OBJECT-TYPE
			SYNTAX BitFail
			MAX-ACCESS read-only
			STATUS current
			DESCRIPTION
				"PMT error (Fist priority  parameter 1.5)"
		::= { isw3000c01v2Entry 331 }

		-- 1.3.6.1.4.1.10106.3.101291.1.1.332
		isw3000c01v2PmtError2TrapEnable OBJECT-TYPE
			SYNTAX AlarmEnable
			MAX-ACCESS read-write
			STATUS current
			DESCRIPTION
				"PMT error (Fist priority  parameter 1.5) Trap Enable"
		::= { isw3000c01v2Entry 332 }

		-- 1.3.6.1.4.1.10106.3.101291.1.1.333
		isw3000c01v2PidError2 OBJECT-TYPE
			SYNTAX BitFail
			MAX-ACCESS read-only
			STATUS current
			DESCRIPTION
				"PID error (Fist priority  parameter 1.6)"
		::= { isw3000c01v2Entry 333 }

		-- 1.3.6.1.4.1.10106.3.101291.1.1.334
		isw3000c01v2PidError2TrapEnable OBJECT-TYPE
			SYNTAX AlarmEnable
			MAX-ACCESS read-write
			STATUS current
			DESCRIPTION
				"PID error (Fist priority  parameter 1.6) Trap Enable"
		::= { isw3000c01v2Entry 334 }

		-- 1.3.6.1.4.1.10106.3.101291.1.1.335
		isw3000c01v2MipError2 OBJECT-TYPE
			SYNTAX BitFail
			MAX-ACCESS read-only
			STATUS current
			DESCRIPTION
				"MIP error. DVB-T compliant"
		::= { isw3000c01v2Entry 335 }

		-- 1.3.6.1.4.1.10106.3.101291.1.1.336
		isw3000c01v2MipError2TrapEnable OBJECT-TYPE
			SYNTAX AlarmEnable
			MAX-ACCESS read-write
			STATUS current
			DESCRIPTION
				"MIP error. DVB-T compliant Trap Enable"
		::= { isw3000c01v2Entry 336 }

		-- 1.3.6.1.4.1.10106.3.101291.1.1.337
		isw3000c01v2GlobalError2 OBJECT-TYPE
			SYNTAX BitFail
			MAX-ACCESS read-only
			STATUS current
			DESCRIPTION
				"Global fail"
		::= { isw3000c01v2Entry 337 }

		-- 1.3.6.1.4.1.10106.3.101291.1.1.338
		isw3000c01v2GlobalError2TrapEnable OBJECT-TYPE
			SYNTAX AlarmEnable
			MAX-ACCESS read-write
			STATUS current
			DESCRIPTION
				"Global fail Trap Enable"
		::= { isw3000c01v2Entry 338 }

		-- 1.3.6.1.4.1.10106.3.101291.1.1.339
		isw3000c01v2GlobalError2G OBJECT-TYPE
			SYNTAX BitFail
			MAX-ACCESS read-only
			STATUS current
			DESCRIPTION
				"Global fail TS 2"
		::= { isw3000c01v2Entry 339 }

		-- 1.3.6.1.4.1.10106.3.101291.1.1.341
		isw3000c01v2IpRxAddress3 OBJECT-TYPE
			SYNTAX Uint8
			MAX-ACCESS read-only
			STATUS current
			DESCRIPTION
				"RX packets source IP address (3)"
		::= { isw3000c01v2Entry 341 }

		-- 1.3.6.1.4.1.10106.3.101291.1.1.343
		isw3000c01v2IpRxAddress2 OBJECT-TYPE
			SYNTAX Uint8
			MAX-ACCESS read-only
			STATUS current
			DESCRIPTION
				"RX packets source IP address (2)"
		::= { isw3000c01v2Entry 343 }

		-- 1.3.6.1.4.1.10106.3.101291.1.1.345
		isw3000c01v2IpRxAddress1 OBJECT-TYPE
			SYNTAX Uint8
			MAX-ACCESS read-only
			STATUS current
			DESCRIPTION
				"RX packets source IP address (1)"
		::= { isw3000c01v2Entry 345 }

		-- 1.3.6.1.4.1.10106.3.101291.1.1.347
		isw3000c01v2IpRxAddress0 OBJECT-TYPE
			SYNTAX Uint8
			MAX-ACCESS read-only
			STATUS current
			DESCRIPTION
				"RX packets source IP address (0)"
		::= { isw3000c01v2Entry 347 }

		-- 1.3.6.1.4.1.10106.3.101291.1.1.349
		isw3000c01v2IpRxPort OBJECT-TYPE
			SYNTAX Uint16
			MAX-ACCESS read-only
			STATUS current
			DESCRIPTION
				"RX packets UDP source port"
		::= { isw3000c01v2Entry 349 }

		-- 1.3.6.1.4.1.10106.3.101291.1.1.351
		isw3000c01v2LParam OBJECT-TYPE
			SYNTAX Uint5
			MAX-ACCESS read-only
			STATUS current
			DESCRIPTION
				"L parameter (FEC mode columns)"
		::= { isw3000c01v2Entry 351 }

		-- 1.3.6.1.4.1.10106.3.101291.1.1.353
		isw3000c01v2FecMode OBJECT-TYPE
			SYNTAX FecMode
			MAX-ACCESS read-only
			STATUS current
			DESCRIPTION
				"Protocol"
		::= { isw3000c01v2Entry 353 }

		-- 1.3.6.1.4.1.10106.3.101291.1.1.355
		isw3000c01v2PacketSize OBJECT-TYPE
			SYNTAX Bit02041188
			MAX-ACCESS read-only
			STATUS current
			DESCRIPTION
				"Bytes in TS packets"
		::= { isw3000c01v2Entry 355 }

		-- 1.3.6.1.4.1.10106.3.101291.1.1.357
		isw3000c01v2DParam OBJECT-TYPE
			SYNTAX Uint5
			MAX-ACCESS read-only
			STATUS current
			DESCRIPTION
				"D parameter (FEC mode rows)"
		::= { isw3000c01v2Entry 357 }

		-- 1.3.6.1.4.1.10106.3.101291.1.1.359
		isw3000c01v2TsPckInIpPck OBJECT-TYPE
			SYNTAX Uint3
			MAX-ACCESS read-only
			STATUS current
			DESCRIPTION
				"TS packets in each IP packet"
		::= { isw3000c01v2Entry 359 }

		-- 1.3.6.1.4.1.10106.3.101291.1.1.361
		isw3000c01v2PacketRate OBJECT-TYPE
			SYNTAX PacketRate
			MAX-ACCESS read-only
			STATUS current
			DESCRIPTION
				"IP packet rate"
		::= { isw3000c01v2Entry 361 }

		-- 1.3.6.1.4.1.10106.3.101291.1.1.363
		isw3000c01v2TimeSinceReset OBJECT-TYPE
			SYNTAX TimeS4
			MAX-ACCESS read-only
			STATUS current
			DESCRIPTION
				"Elapsed time from last reset"
		::= { isw3000c01v2Entry 363 }

		-- 1.3.6.1.4.1.10106.3.101291.1.1.365
		isw3000c01v2LostIpPck OBJECT-TYPE
			SYNTAX Uint16
			MAX-ACCESS read-only
			STATUS current
			DESCRIPTION
				"Lost IP packets"
		::= { isw3000c01v2Entry 365 }

		-- 1.3.6.1.4.1.10106.3.101291.1.1.367
		isw3000c01v2RecoveredIpPck OBJECT-TYPE
			SYNTAX Uint16
			MAX-ACCESS read-only
			STATUS current
			DESCRIPTION
				"Recovered IP packets"
		::= { isw3000c01v2Entry 367 }

		-- 1.3.6.1.4.1.10106.3.101291.1.1.369
		isw3000c01v2BadCrcPck OBJECT-TYPE
			SYNTAX Uint16
			MAX-ACCESS read-only
			STATUS current
			DESCRIPTION
				"Bad CRC packets"
		::= { isw3000c01v2Entry 369 }

		-- 1.3.6.1.4.1.10106.3.101291.1.1.371
		isw3000c01v2OutOrdIpPck OBJECT-TYPE
			SYNTAX Uint16
			MAX-ACCESS read-only
			STATUS current
			DESCRIPTION
				"Out of order IP packets"
		::= { isw3000c01v2Entry 371 }

		-- 1.3.6.1.4.1.10106.3.101291.1.1.373
		isw3000c01v2FecRate OBJECT-TYPE
			SYNTAX PacketRate
			MAX-ACCESS read-only
			STATUS current
			DESCRIPTION
				"FEC packet rate"
		::= { isw3000c01v2Entry 373 }

		-- 1.3.6.1.4.1.10106.3.101291.1.1.375
		isw3000c01v2Link OBJECT-TYPE
			SYNTAX IpaEtherStat
			MAX-ACCESS read-only
			STATUS current
			DESCRIPTION
				"Ethernet conection status"
		::= { isw3000c01v2Entry 375 }

		-- 1.3.6.1.4.1.10106.3.101291.1.1.377
		isw3000c01v2System OBJECT-TYPE
			SYNTAX IpaEtherSys
			MAX-ACCESS read-only
			STATUS current
			DESCRIPTION
				"Ethernet conection system"
		::= { isw3000c01v2Entry 377 }

		-- 1.3.6.1.4.1.10106.3.101291.1.1.379
		isw3000c01v2DestAvailable OBJECT-TYPE
			SYNTAX Bit0No1Yes
			MAX-ACCESS read-only
			STATUS current
			DESCRIPTION
				"Destination IP available"
		::= { isw3000c01v2Entry 379 }

		-- 1.3.6.1.4.1.10106.3.101291.1.1.381
		isw3000c01v2Ts1BufOvf OBJECT-TYPE
			SYNTAX BitFail
			MAX-ACCESS read-only
			STATUS current
			DESCRIPTION
				"Buffer overflow"
		::= { isw3000c01v2Entry 381 }

		-- 1.3.6.1.4.1.10106.3.101291.1.1.383
		isw3000c01v2Ts2BufOvf OBJECT-TYPE
			SYNTAX BitFail
			MAX-ACCESS read-only
			STATUS current
			DESCRIPTION
				"Buffer overflow"
		::= { isw3000c01v2Entry 383 }

		-- 1.3.6.1.4.1.10106.3.101291.1.1.385
		isw3000c01v2Ts1BufUnd OBJECT-TYPE
			SYNTAX BitFail
			MAX-ACCESS read-only
			STATUS current
			DESCRIPTION
				"Buffer underflow"
		::= { isw3000c01v2Entry 385 }

		-- 1.3.6.1.4.1.10106.3.101291.1.1.387
		isw3000c01v2Ts2BufUnd OBJECT-TYPE
			SYNTAX BitFail
			MAX-ACCESS read-only
			STATUS current
			DESCRIPTION
				"Buffer underflow"
		::= { isw3000c01v2Entry 387 }

		-- 1.3.6.1.4.1.10106.3.101291.1.1.389
		isw3000c01v2BufferStatus OBJECT-TYPE
			SYNTAX Rate1
			MAX-ACCESS read-only
			STATUS current
			DESCRIPTION
				"Buffer filling status"
		::= { isw3000c01v2Entry 389 }

		-- 1.3.6.1.4.1.10106.3.101291.1.1.391
		isw3000c01v2PingStatus OBJECT-TYPE
			SYNTAX IpaPingStat
			MAX-ACCESS read-only
			STATUS current
			DESCRIPTION
				"Ping status"
		::= { isw3000c01v2Entry 391 }

		-- 1.3.6.1.4.1.10106.3.101291.1.1.393
		isw3000c01v2SerialNo OBJECT-TYPE
			SYNTAX SerialNo
			MAX-ACCESS read-only
			STATUS current
			DESCRIPTION
				"Serial number"
		::= { isw3000c01v2Entry 393 }

		-- 1.3.6.1.4.1.10106.3.101291.1.1.395
		isw3000c01v2MaxDelayTxIp OBJECT-TYPE
			SYNTAX TimeX10Ms
			MAX-ACCESS read-write
			STATUS current
			DESCRIPTION
				"Time before starting to transmit after recovering signal"
		::= { isw3000c01v2Entry 395 }

		-- 1.3.6.1.4.1.10106.3.101291.1.1.397
		isw3000c01v2InpFailMode OBJECT-TYPE
			SYNTAX Bit0Yes1No
			MAX-ACCESS read-write
			STATUS current
			DESCRIPTION
				"Selects if the output is muted when all the inputs fail"
		::= { isw3000c01v2Entry 397 }

		-- 1.3.6.1.4.1.10106.3.522601
		imb2000c01v1 OBJECT IDENTIFIER ::= { albalaProducts 522601 }

		-- 1.3.6.1.4.1.10106.3.522601.1
		imb2000c01v1Table  OBJECT-TYPE
			SYNTAX SEQUENCE OF Imb2000c01v1Entry
			MAX-ACCESS not-accessible
			STATUS current
			DESCRIPTION
				"Module  IMB2000C01V1 Table"
			::= { imb2000c01v1 1 }

		-- 1.3.6.1.4.1.10106.3.522601.1.1
		imb2000c01v1Entry  OBJECT-TYPE
			SYNTAX Imb2000c01v1Entry
			MAX-ACCESS not-accessible
			STATUS current
			DESCRIPTION
				"Module IMB2000C01V1 Entry"
			INDEX { imb2000c01v1Index }
			::= { imb2000c01v1Table 1 }

			Imb2000c01v1Entry ::=
			SEQUENCE {
				imb2000c01v1Index
				ModuleIndex,
				imb2000c01v1SyncInterface
				SyncMode,
				imb2000c01v1StatMode
				Bit01s1Total,
				imb2000c01v1StatReset
				Bit0No1Yes,
				imb2000c01v1Aes67Enable
				Aes67Discovery,
				imb2000c01v1TtlTx
				Uint8,
				imb2000c01v1TxSrPort
				Uint16,
				imb2000c01v1EthMode1
				EthMode2000,
				imb2000c01v1SpeedForce1
				Bit0Ann1For,
				imb2000c01v1Address12En
				Bit0No1Yes,
				imb2000c01v1EthMode2
				EthMode2000,
				imb2000c01v1SpeedForce2
				Bit0Ann1For,
				imb2000c01v1Address22En
				Bit0No1Yes,
				imb2000c01v1LocalIpGway3
				Uint8,
				imb2000c01v1LocalIpGway2
				Uint8,
				imb2000c01v1LocalIpGway1
				Uint8,
				imb2000c01v1LocalIpGway0
				Uint8,
				imb2000c01v1Slot1M2sIns
				BitMask,
				imb2000c01v1Slot2M2sIns
				BitMask,
				imb2000c01v1Slot3M2sIns
				BitMask,
				imb2000c01v1Slot4M2sIns
				BitMask,
				imb2000c01v1Slot5M2sIns
				BitMask,
				imb2000c01v1Slot6M2sIns
				BitMask,
				imb2000c01v1Slot7M2sIns
				BitMask,
				imb2000c01v1Slot8M2sIns
				BitMask,
				imb2000c01v1Profile
				PtpProfile,
				imb2000c01v1DomainNumber
				Uint8,
				imb2000c01v1LogAnnounceInt
				PtpInterval,
				imb2000c01v1LogSyncInt
				PtpInterval,
				imb2000c01v1LogMinDRInt
				PtpInterval,
				imb2000c01v1StreamOk1
				BitFailN,
				imb2000c01v1BufferUnderf1
				BitFail,
				imb2000c01v1BufferOverf1
				BitFail,
				imb2000c01v1MalformedPck1
				BitFail,
				imb2000c01v1RxFail1
				BitFail,
				imb2000c01v1Rx1PckRate
				PacketRate,
				imb2000c01v1Rx1LostIpPk
				PacketNum,
				imb2000c01v1Rx1DupIpPck
				PacketNum,
				imb2000c01v1MaxBuffLev1
				BufferPercentag,
				imb2000c01v1MinBuffLev1
				BufferPercentag,
				imb2000c01v1StreamOk2
				BitFailN,
				imb2000c01v1BufferUnderf2
				BitFail,
				imb2000c01v1BufferOverf2
				BitFail,
				imb2000c01v1MalformedPck2
				BitFail,
				imb2000c01v1RxFail2
				BitFail,
				imb2000c01v1Rx2PckRate
				PacketRate,
				imb2000c01v1Rx2LostIpPk
				PacketNum,
				imb2000c01v1Rx2DupIpPck
				PacketNum,
				imb2000c01v1MaxBuffLev2
				BufferPercentag,
				imb2000c01v1MinBuffLev2
				BufferPercentag,
				imb2000c01v1StreamOk3
				BitFailN,
				imb2000c01v1BufferUnderf3
				BitFail,
				imb2000c01v1BufferOverf3
				BitFail,
				imb2000c01v1MalformedPck3
				BitFail,
				imb2000c01v1RxFail3
				BitFail,
				imb2000c01v1Rx3PckRate
				PacketRate,
				imb2000c01v1Rx3LostIpPk
				PacketNum,
				imb2000c01v1Rx3DupIpPck
				PacketNum,
				imb2000c01v1MaxBuffLev3
				BufferPercentag,
				imb2000c01v1MinBuffLev3
				BufferPercentag,
				imb2000c01v1StreamOk4
				BitFailN,
				imb2000c01v1BufferUnderf4
				BitFail,
				imb2000c01v1BufferOverf4
				BitFail,
				imb2000c01v1MalformedPck4
				BitFail,
				imb2000c01v1RxFail4
				BitFail,
				imb2000c01v1Rx4PckRate
				PacketRate,
				imb2000c01v1Rx4LostIpPk
				PacketNum,
				imb2000c01v1Rx4DupIpPck
				PacketNum,
				imb2000c01v1MaxBuffLev4
				BufferPercentag,
				imb2000c01v1MinBuffLev4
				BufferPercentag,
				imb2000c01v1StreamOk5
				BitFailN,
				imb2000c01v1BufferUnderf5
				BitFail,
				imb2000c01v1BufferOverf5
				BitFail,
				imb2000c01v1MalformedPck5
				BitFail,
				imb2000c01v1RxFail5
				BitFail,
				imb2000c01v1Rx5PckRate
				PacketRate,
				imb2000c01v1Rx5LostIpPk
				PacketNum,
				imb2000c01v1Rx5DupIpPck
				PacketNum,
				imb2000c01v1MaxBuffLev5
				BufferPercentag,
				imb2000c01v1MinBuffLev5
				BufferPercentag,
				imb2000c01v1StreamOk6
				BitFailN,
				imb2000c01v1BufferUnderf6
				BitFail,
				imb2000c01v1BufferOverf6
				BitFail,
				imb2000c01v1MalformedPck6
				BitFail,
				imb2000c01v1RxFail6
				BitFail,
				imb2000c01v1Rx6PckRate
				PacketRate,
				imb2000c01v1Rx6LostIpPk
				PacketNum,
				imb2000c01v1Rx6DupIpPck
				PacketNum,
				imb2000c01v1MaxBuffLev6
				BufferPercentag,
				imb2000c01v1MinBuffLev6
				BufferPercentag,
				imb2000c01v1StreamOk7
				BitFailN,
				imb2000c01v1BufferUnderf7
				BitFail,
				imb2000c01v1BufferOverf7
				BitFail,
				imb2000c01v1MalformedPck7
				BitFail,
				imb2000c01v1RxFail7
				BitFail,
				imb2000c01v1Rx7PckRate
				PacketRate,
				imb2000c01v1Rx7LostIpPk
				PacketNum,
				imb2000c01v1Rx7DupIpPck
				PacketNum,
				imb2000c01v1MaxBuffLev7
				BufferPercentag,
				imb2000c01v1MinBuffLev7
				BufferPercentag,
				imb2000c01v1StreamOk8
				BitFailN,
				imb2000c01v1BufferUnderf8
				BitFail,
				imb2000c01v1BufferOverf8
				BitFail,
				imb2000c01v1MalformedPck8
				BitFail,
				imb2000c01v1RxFail8
				BitFail,
				imb2000c01v1Rx8PckRate
				PacketRate,
				imb2000c01v1Rx8LostIpPk
				PacketNum,
				imb2000c01v1Rx8DupIpPck
				PacketNum,
				imb2000c01v1MaxBuffLev8
				BufferPercentag,
				imb2000c01v1MinBuffLev8
				BufferPercentag,
				imb2000c01v1StreamOk9
				BitFailN,
				imb2000c01v1BufferUnderf9
				BitFail,
				imb2000c01v1BufferOverf9
				BitFail,
				imb2000c01v1MalformedPck9
				BitFail,
				imb2000c01v1RxFail9
				BitFail,
				imb2000c01v1Rx9PckRate
				PacketRate,
				imb2000c01v1Rx9LostIpPk
				PacketNum,
				imb2000c01v1Rx9DupIpPck
				PacketNum,
				imb2000c01v1MaxBuffLev9
				BufferPercentag,
				imb2000c01v1MinBuffLev9
				BufferPercentag,
				imb2000c01v1StreamOk10
				BitFailN,
				imb2000c01v1BufferUnderf10
				BitFail,
				imb2000c01v1BufferOverf10
				BitFail,
				imb2000c01v1MalformedPck10
				BitFail,
				imb2000c01v1RxFail10
				BitFail,
				imb2000c01v1Rx10PckRate
				PacketRate,
				imb2000c01v1Rx10LostIpPk
				PacketNum,
				imb2000c01v1Rx10DupIpPck
				PacketNum,
				imb2000c01v1MaxBuffLev10
				BufferPercentag,
				imb2000c01v1MinBuffLev10
				BufferPercentag,
				imb2000c01v1StreamOk11
				BitFailN,
				imb2000c01v1BufferUnderf11
				BitFail,
				imb2000c01v1BufferOverf11
				BitFail,
				imb2000c01v1MalformedPck11
				BitFail,
				imb2000c01v1RxFail11
				BitFail,
				imb2000c01v1Rx11PckRate
				PacketRate,
				imb2000c01v1Rx11LostIpPk
				PacketNum,
				imb2000c01v1Rx11DupIpPck
				PacketNum,
				imb2000c01v1MaxBuffLev11
				BufferPercentag,
				imb2000c01v1MinBuffLev11
				BufferPercentag,
				imb2000c01v1StreamOk12
				BitFailN,
				imb2000c01v1BufferUnderf12
				BitFail,
				imb2000c01v1BufferOverf12
				BitFail,
				imb2000c01v1MalformedPck12
				BitFail,
				imb2000c01v1RxFail12
				BitFail,
				imb2000c01v1Rx12PckRate
				PacketRate,
				imb2000c01v1Rx12LostIpPk
				PacketNum,
				imb2000c01v1Rx12DupIpPck
				PacketNum,
				imb2000c01v1MaxBuffLev12
				BufferPercentag,
				imb2000c01v1MinBuffLev12
				BufferPercentag,
				imb2000c01v1StreamOk13
				BitFailN,
				imb2000c01v1BufferUnderf13
				BitFail,
				imb2000c01v1BufferOverf13
				BitFail,
				imb2000c01v1MalformedPck13
				BitFail,
				imb2000c01v1RxFail13
				BitFail,
				imb2000c01v1Rx13PckRate
				PacketRate,
				imb2000c01v1Rx13LostIpPk
				PacketNum,
				imb2000c01v1Rx13DupIpPck
				PacketNum,
				imb2000c01v1MaxBuffLev13
				BufferPercentag,
				imb2000c01v1MinBuffLev13
				BufferPercentag,
				imb2000c01v1StreamOk14
				BitFailN,
				imb2000c01v1BufferUnderf14
				BitFail,
				imb2000c01v1BufferOverf14
				BitFail,
				imb2000c01v1MalformedPck14
				BitFail,
				imb2000c01v1RxFail14
				BitFail,
				imb2000c01v1Rx14PckRate
				PacketRate,
				imb2000c01v1Rx14LostIpPk
				PacketNum,
				imb2000c01v1Rx14DupIpPck
				PacketNum,
				imb2000c01v1MaxBuffLev14
				BufferPercentag,
				imb2000c01v1MinBuffLev14
				BufferPercentag,
				imb2000c01v1StreamOk15
				BitFailN,
				imb2000c01v1BufferUnderf15
				BitFail,
				imb2000c01v1BufferOverf15
				BitFail,
				imb2000c01v1MalformedPck15
				BitFail,
				imb2000c01v1RxFail15
				BitFail,
				imb2000c01v1Rx15PckRate
				PacketRate,
				imb2000c01v1Rx15LostIpPk
				PacketNum,
				imb2000c01v1Rx15DupIpPck
				PacketNum,
				imb2000c01v1MaxBuffLev15
				BufferPercentag,
				imb2000c01v1MinBuffLev15
				BufferPercentag,
				imb2000c01v1StreamOk16
				BitFailN,
				imb2000c01v1BufferUnderf16
				BitFail,
				imb2000c01v1BufferOverf16
				BitFail,
				imb2000c01v1MalformedPck16
				BitFail,
				imb2000c01v1RxFail16
				BitFail,
				imb2000c01v1Rx16PckRate
				PacketRate,
				imb2000c01v1Rx16LostIpPk
				PacketNum,
				imb2000c01v1Rx16DupIpPck
				PacketNum,
				imb2000c01v1MaxBuffLev16
				BufferPercentag,
				imb2000c01v1MinBuffLev16
				BufferPercentag,
				imb2000c01v1EnWc48k
				BitMask,
				imb2000c01v1EnBusRefTx
				Bit0No1Yes,
				imb2000c01v1Slot1S2mPres
				BitAct,
				imb2000c01v1Slot2S2mPres
				BitAct,
				imb2000c01v1Slot3S2mPres
				BitAct,
				imb2000c01v1Slot4S2mPres
				BitAct,
				imb2000c01v1Slot5S2mPres
				BitAct,
				imb2000c01v1Slot6S2mPres
				BitAct,
				imb2000c01v1Slot7S2mPres
				BitAct,
				imb2000c01v1Slot8S2mPres
				BitAct,
				imb2000c01v1BusRxFail
				BitFail,
				imb2000c01v1MadiTxNCh
				MadiNCh,
				imb2000c01v1ShufOk
				BitFailN,
				imb2000c01v1LocalIp1Add3
				Uint8,
				imb2000c01v1LocalIp1Add2
				Uint8,
				imb2000c01v1LocalIp1Add1
				Uint8,
				imb2000c01v1LocalIp1Add0
				Uint8,
				imb2000c01v1LocalIp1Msk3
				Uint8,
				imb2000c01v1LocalIp1Msk2
				Uint8,
				imb2000c01v1LocalIp1Msk1
				Uint8,
				imb2000c01v1LocalIp1Msk0
				Uint8,
				imb2000c01v1Vlan1Enable
				Bit0No1Yes,
				imb2000c01v1VlanPriority1
				Uint3,
				imb2000c01v1Vlan1Id
				Uint12,
				imb2000c01v1LocalIp2Add3
				Uint8,
				imb2000c01v1LocalIp2Add2
				Uint8,
				imb2000c01v1LocalIp2Add1
				Uint8,
				imb2000c01v1LocalIp2Add0
				Uint8,
				imb2000c01v1LocalIp2Msk3
				Uint8,
				imb2000c01v1LocalIp2Msk2
				Uint8,
				imb2000c01v1LocalIp2Msk1
				Uint8,
				imb2000c01v1LocalIp2Msk0
				Uint8,
				imb2000c01v1Vlan2Enable
				Bit0No1Yes,
				imb2000c01v1VlanPriority2
				Uint3,
				imb2000c01v1Vlan2Id
				Uint12,
				imb2000c01v1LocalIp3Add3
				Uint8,
				imb2000c01v1LocalIp3Add2
				Uint8,
				imb2000c01v1LocalIp3Add1
				Uint8,
				imb2000c01v1LocalIpAdd0
				Uint8,
				imb2000c01v1LocalIp3Msk3
				Uint8,
				imb2000c01v1LocalIp3Msk2
				Uint8,
				imb2000c01v1LocalIp3Msk1
				Uint8,
				imb2000c01v1LocalIp3Msk0
				Uint8,
				imb2000c01v1Vlan3Enable
				Bit0No1Yes,
				imb2000c01v1VlanPriority3
				Uint3,
				imb2000c01v1Vlan3Id
				Uint12,
				imb2000c01v1LocalIp4Add3
				Uint8,
				imb2000c01v1LocalIp4Add2
				Uint8,
				imb2000c01v1LocalIp4Add1
				Uint8,
				imb2000c01v1LocalIp4Add0
				Uint8,
				imb2000c01v1LocalIp4Msk3
				Uint8,
				imb2000c01v1LocalIp4Msk2
				Uint8,
				imb2000c01v1LocalIp4Msk1
				Uint8,
				imb2000c01v1LocalIp4Msk0
				Uint8,
				imb2000c01v1Vlan4Enable
				Bit0No1Yes,
				imb2000c01v1VlanPriority4
				Uint3,
				imb2000c01v1Vlan4Id
				Uint12,
				imb2000c01v1SysError
				SysError0,
				imb2000c01v1PtpIntSelected
				PtpStatus,
				imb2000c01v1TxWorkinStat1
				BitFailN,
				imb2000c01v1ArpValid1
				BitFailN,
				imb2000c01v1IcmpError1
				BitFailN,
				imb2000c01v1TxWorkinStat2
				BitFailN,
				imb2000c01v1ArpValid2
				BitFailN,
				imb2000c01v1IcmpError2
				BitFailN,
				imb2000c01v1TxWorkinStat3
				BitFailN,
				imb2000c01v1ArpValid3
				BitFailN,
				imb2000c01v1IcmpError3
				BitFailN,
				imb2000c01v1TxWorkinStat4
				BitFailN,
				imb2000c01v1ArpValid4
				BitFailN,
				imb2000c01v1IcmpError4
				BitFailN,
				imb2000c01v1TxWorkinStat5
				BitFailN,
				imb2000c01v1ArpValid5
				BitFailN,
				imb2000c01v1IcmpError5
				BitFailN,
				imb2000c01v1TxWorkinStat6
				BitFailN,
				imb2000c01v1ArpValid6
				BitFailN,
				imb2000c01v1IcmpError6
				BitFailN,
				imb2000c01v1TxWorkinStat7
				BitFailN,
				imb2000c01v1ArpValid7
				BitFailN,
				imb2000c01v1IcmpError7
				BitFailN,
				imb2000c01v1TxWorkinStat8
				BitFailN,
				imb2000c01v1ArpValid8
				BitFailN,
				imb2000c01v1IcmpError8
				BitFailN,
				imb2000c01v1PtpState
				PtpState,
				imb2000c01v1MadiRxOk
				BitFailN,
				imb2000c01v1MadiRxNCh
				Uint7,
				imb2000c01v1ClkStatus
				ClkStatus,
				imb2000c01v1ClockOffset
				TimeX1Us,
				imb2000c01v1ClockDelay
				TimeX1Us,
				imb2000c01v1RxTimeRst
				TimeS6,
				imb2000c01v1Link1
				Ipa2EtherStat,
				imb2000c01v1System1
				Ipa2EtherSys,
				imb2000c01v1Link2
				Ipa2EtherStat,
				imb2000c01v1System2
				Ipa2EtherSys,
				imb2000c01v1SerialNo
				SerialNo
			 }

		-- 1.3.6.1.4.1.10106.3.101291.1.1.1
		imb2000c01v1Index OBJECT-TYPE
			SYNTAX ModuleIndex
			MAX-ACCESS read-only
			STATUS current
			DESCRIPTION
				"Index of IMB2000C01V1 Table"
		::= { imb2000c01v1Entry 1 }

		-- 1.3.6.1.4.1.10106.3.101291.1.1.3
		imb2000c01v1SyncInterface OBJECT-TYPE
			SYNTAX SyncMode
			MAX-ACCESS read-write
			STATUS current
			DESCRIPTION
				"Syncrhonism interface"
		::= { imb2000c01v1Entry 3 }

		-- 1.3.6.1.4.1.10106.3.101291.1.1.5
		imb2000c01v1StatMode OBJECT-TYPE
			SYNTAX Bit01s1Total
			MAX-ACCESS read-write
			STATUS current
			DESCRIPTION
				"Allows selecting the statistics mode"
		::= { imb2000c01v1Entry 5 }

		-- 1.3.6.1.4.1.10106.3.101291.1.1.7
		imb2000c01v1StatReset OBJECT-TYPE
			SYNTAX Bit0No1Yes
			MAX-ACCESS read-write
			STATUS current
			DESCRIPTION
				"Allows reseting the statistics measurements"
		::= { imb2000c01v1Entry 7 }

		-- 1.3.6.1.4.1.10106.3.101291.1.1.9
		imb2000c01v1Aes67Enable OBJECT-TYPE
			SYNTAX Aes67Discovery
			MAX-ACCESS read-write
			STATUS current
			DESCRIPTION
				"AES67 protocol"
		::= { imb2000c01v1Entry 9 }

		-- 1.3.6.1.4.1.10106.3.101291.1.1.11
		imb2000c01v1TtlTx OBJECT-TYPE
			SYNTAX Uint8
			MAX-ACCESS read-write
			STATUS current
			DESCRIPTION
				"Time To Life for transmitted packets"
		::= { imb2000c01v1Entry 11 }

		-- 1.3.6.1.4.1.10106.3.101291.1.1.13
		imb2000c01v1TxSrPort OBJECT-TYPE
			SYNTAX Uint16
			MAX-ACCESS read-write
			STATUS current
			DESCRIPTION
				"Source port"
		::= { imb2000c01v1Entry 13 }

		-- 1.3.6.1.4.1.10106.3.101291.1.1.15
		imb2000c01v1EthMode1 OBJECT-TYPE
			SYNTAX EthMode2000
			MAX-ACCESS read-write
			STATUS current
			DESCRIPTION
				"Allows selecting the Ethernet operating mode"
		::= { imb2000c01v1Entry 15 }

		-- 1.3.6.1.4.1.10106.3.101291.1.1.17
		imb2000c01v1SpeedForce1 OBJECT-TYPE
			SYNTAX Bit0Ann1For
			MAX-ACCESS read-write
			STATUS current
			DESCRIPTION
				"Allows selecting if the speed/mode is forced or announced for autonegotiation"
		::= { imb2000c01v1Entry 17 }

		-- 1.3.6.1.4.1.10106.3.101291.1.1.19
		imb2000c01v1Address12En OBJECT-TYPE
			SYNTAX Bit0No1Yes
			MAX-ACCESS read-write
			STATUS current
			DESCRIPTION
				"Interface 2 enable"
		::= { imb2000c01v1Entry 19 }

		-- 1.3.6.1.4.1.10106.3.101291.1.1.21
		imb2000c01v1EthMode2 OBJECT-TYPE
			SYNTAX EthMode2000
			MAX-ACCESS read-write
			STATUS current
			DESCRIPTION
				"Allows selecting the Ethernet operating mode"
		::= { imb2000c01v1Entry 21 }

		-- 1.3.6.1.4.1.10106.3.101291.1.1.23
		imb2000c01v1SpeedForce2 OBJECT-TYPE
			SYNTAX Bit0Ann1For
			MAX-ACCESS read-write
			STATUS current
			DESCRIPTION
				"Allows selecting if the speed/mode is forced or announced for autonegotiation"
		::= { imb2000c01v1Entry 23 }

		-- 1.3.6.1.4.1.10106.3.101291.1.1.25
		imb2000c01v1Address22En OBJECT-TYPE
			SYNTAX Bit0No1Yes
			MAX-ACCESS read-write
			STATUS current
			DESCRIPTION
				"Interface 2 enable"
		::= { imb2000c01v1Entry 25 }

		-- 1.3.6.1.4.1.10106.3.101291.1.1.27
		imb2000c01v1LocalIpGway3 OBJECT-TYPE
			SYNTAX Uint8
			MAX-ACCESS read-write
			STATUS current
			DESCRIPTION
				"Gateway IP address (3)"
		::= { imb2000c01v1Entry 27 }

		-- 1.3.6.1.4.1.10106.3.101291.1.1.29
		imb2000c01v1LocalIpGway2 OBJECT-TYPE
			SYNTAX Uint8
			MAX-ACCESS read-write
			STATUS current
			DESCRIPTION
				"Gateway IP address (2)"
		::= { imb2000c01v1Entry 29 }

		-- 1.3.6.1.4.1.10106.3.101291.1.1.31
		imb2000c01v1LocalIpGway1 OBJECT-TYPE
			SYNTAX Uint8
			MAX-ACCESS read-write
			STATUS current
			DESCRIPTION
				"Gateway IP address (1)"
		::= { imb2000c01v1Entry 31 }

		-- 1.3.6.1.4.1.10106.3.101291.1.1.33
		imb2000c01v1LocalIpGway0 OBJECT-TYPE
			SYNTAX Uint8
			MAX-ACCESS read-write
			STATUS current
			DESCRIPTION
				"Gateway IP address (0)"
		::= { imb2000c01v1Entry 33 }

		-- 1.3.6.1.4.1.10106.3.101291.1.1.35
		imb2000c01v1Slot1M2sIns OBJECT-TYPE
			SYNTAX BitMask
			MAX-ACCESS read-write
			STATUS current
			DESCRIPTION
				"Backplane slot 1 M2S insert"
		::= { imb2000c01v1Entry 35 }

		-- 1.3.6.1.4.1.10106.3.101291.1.1.37
		imb2000c01v1Slot2M2sIns OBJECT-TYPE
			SYNTAX BitMask
			MAX-ACCESS read-write
			STATUS current
			DESCRIPTION
				"Backplane slot 2 M2S insert"
		::= { imb2000c01v1Entry 37 }

		-- 1.3.6.1.4.1.10106.3.101291.1.1.39
		imb2000c01v1Slot3M2sIns OBJECT-TYPE
			SYNTAX BitMask
			MAX-ACCESS read-write
			STATUS current
			DESCRIPTION
				"Backplane slot 3 M2S insert"
		::= { imb2000c01v1Entry 39 }

		-- 1.3.6.1.4.1.10106.3.101291.1.1.41
		imb2000c01v1Slot4M2sIns OBJECT-TYPE
			SYNTAX BitMask
			MAX-ACCESS read-write
			STATUS current
			DESCRIPTION
				"Backplane slot 4 M2S insert"
		::= { imb2000c01v1Entry 41 }

		-- 1.3.6.1.4.1.10106.3.101291.1.1.43
		imb2000c01v1Slot5M2sIns OBJECT-TYPE
			SYNTAX BitMask
			MAX-ACCESS read-write
			STATUS current
			DESCRIPTION
				"Backplane slot 5 M2S insert"
		::= { imb2000c01v1Entry 43 }

		-- 1.3.6.1.4.1.10106.3.101291.1.1.45
		imb2000c01v1Slot6M2sIns OBJECT-TYPE
			SYNTAX BitMask
			MAX-ACCESS read-write
			STATUS current
			DESCRIPTION
				"Backplane slot 6 M2S insert"
		::= { imb2000c01v1Entry 45 }

		-- 1.3.6.1.4.1.10106.3.101291.1.1.47
		imb2000c01v1Slot7M2sIns OBJECT-TYPE
			SYNTAX BitMask
			MAX-ACCESS read-write
			STATUS current
			DESCRIPTION
				"Backplane slot 7 M2S insert"
		::= { imb2000c01v1Entry 47 }

		-- 1.3.6.1.4.1.10106.3.101291.1.1.49
		imb2000c01v1Slot8M2sIns OBJECT-TYPE
			SYNTAX BitMask
			MAX-ACCESS read-write
			STATUS current
			DESCRIPTION
				"Backplane slot 8 M2S insert"
		::= { imb2000c01v1Entry 49 }

		-- 1.3.6.1.4.1.10106.3.101291.1.1.51
		imb2000c01v1Profile OBJECT-TYPE
			SYNTAX PtpProfile
			MAX-ACCESS read-write
			STATUS current
			DESCRIPTION
				"Allows loading default values of a PTP profile"
		::= { imb2000c01v1Entry 51 }

		-- 1.3.6.1.4.1.10106.3.101291.1.1.53
		imb2000c01v1DomainNumber OBJECT-TYPE
			SYNTAX Uint8
			MAX-ACCESS read-write
			STATUS current
			DESCRIPTION
				"Allows selecting the Domanin number attribute of the local clock"
		::= { imb2000c01v1Entry 53 }

		-- 1.3.6.1.4.1.10106.3.101291.1.1.55
		imb2000c01v1LogAnnounceInt OBJECT-TYPE
			SYNTAX PtpInterval
			MAX-ACCESS read-write
			STATUS current
			DESCRIPTION
				"Allows selecting the mean interval between Announce messages"
		::= { imb2000c01v1Entry 55 }

		-- 1.3.6.1.4.1.10106.3.101291.1.1.57
		imb2000c01v1LogSyncInt OBJECT-TYPE
			SYNTAX PtpInterval
			MAX-ACCESS read-write
			STATUS current
			DESCRIPTION
				"Allows selecting the mean interval between Sync messages"
		::= { imb2000c01v1Entry 57 }

		-- 1.3.6.1.4.1.10106.3.101291.1.1.59
		imb2000c01v1LogMinDRInt OBJECT-TYPE
			SYNTAX PtpInterval
			MAX-ACCESS read-write
			STATUS current
			DESCRIPTION
				"Allows selecting the minimum mean interval between Delay_Req messages"
		::= { imb2000c01v1Entry 59 }

		-- 1.3.6.1.4.1.10106.3.101291.1.1.61
		imb2000c01v1StreamOk1 OBJECT-TYPE
			SYNTAX BitFailN
			MAX-ACCESS read-only
			STATUS current
			DESCRIPTION
				"AES67 stream 1 received"
		::= { imb2000c01v1Entry 61 }

		-- 1.3.6.1.4.1.10106.3.101291.1.1.63
		imb2000c01v1BufferUnderf1 OBJECT-TYPE
			SYNTAX BitFail
			MAX-ACCESS read-only
			STATUS current
			DESCRIPTION
				"Buffer underflow"
		::= { imb2000c01v1Entry 63 }

		-- 1.3.6.1.4.1.10106.3.101291.1.1.65
		imb2000c01v1BufferOverf1 OBJECT-TYPE
			SYNTAX BitFail
			MAX-ACCESS read-only
			STATUS current
			DESCRIPTION
				"Buffer_overflow/TS error"
		::= { imb2000c01v1Entry 65 }

		-- 1.3.6.1.4.1.10106.3.101291.1.1.67
		imb2000c01v1MalformedPck1 OBJECT-TYPE
			SYNTAX BitFail
			MAX-ACCESS read-only
			STATUS current
			DESCRIPTION
				"Malformed packets"
		::= { imb2000c01v1Entry 67 }

		-- 1.3.6.1.4.1.10106.3.101291.1.1.69
		imb2000c01v1RxFail1 OBJECT-TYPE
			SYNTAX BitFail
			MAX-ACCESS read-only
			STATUS current
			DESCRIPTION
				"RX1 stream fail"
		::= { imb2000c01v1Entry 69 }

		-- 1.3.6.1.4.1.10106.3.101291.1.1.71
		imb2000c01v1Rx1PckRate OBJECT-TYPE
			SYNTAX PacketRate
			MAX-ACCESS read-only
			STATUS current
			DESCRIPTION
				"IP packet rate"
		::= { imb2000c01v1Entry 71 }

		-- 1.3.6.1.4.1.10106.3.101291.1.1.73
		imb2000c01v1Rx1LostIpPk OBJECT-TYPE
			SYNTAX PacketNum
			MAX-ACCESS read-only
			STATUS current
			DESCRIPTION
				"Lost IP packets rate"
		::= { imb2000c01v1Entry 73 }

		-- 1.3.6.1.4.1.10106.3.101291.1.1.75
		imb2000c01v1Rx1DupIpPck OBJECT-TYPE
			SYNTAX PacketNum
			MAX-ACCESS read-only
			STATUS current
			DESCRIPTION
				"Duplicated IP packets rate"
		::= { imb2000c01v1Entry 75 }

		-- 1.3.6.1.4.1.10106.3.101291.1.1.77
		imb2000c01v1MaxBuffLev1 OBJECT-TYPE
			SYNTAX BufferPercentag
			MAX-ACCESS read-only
			STATUS current
			DESCRIPTION
				"Maximum buffer level"
		::= { imb2000c01v1Entry 77 }

		-- 1.3.6.1.4.1.10106.3.101291.1.1.79
		imb2000c01v1MinBuffLev1 OBJECT-TYPE
			SYNTAX BufferPercentag
			MAX-ACCESS read-only
			STATUS current
			DESCRIPTION
				"Minimum buffer level"
		::= { imb2000c01v1Entry 79 }

		-- 1.3.6.1.4.1.10106.3.101291.1.1.81
		imb2000c01v1StreamOk2 OBJECT-TYPE
			SYNTAX BitFailN
			MAX-ACCESS read-only
			STATUS current
			DESCRIPTION
				"AES67 stream 2 received"
		::= { imb2000c01v1Entry 81 }

		-- 1.3.6.1.4.1.10106.3.101291.1.1.83
		imb2000c01v1BufferUnderf2 OBJECT-TYPE
			SYNTAX BitFail
			MAX-ACCESS read-only
			STATUS current
			DESCRIPTION
				"Buffer underflow"
		::= { imb2000c01v1Entry 83 }

		-- 1.3.6.1.4.1.10106.3.101291.1.1.85
		imb2000c01v1BufferOverf2 OBJECT-TYPE
			SYNTAX BitFail
			MAX-ACCESS read-only
			STATUS current
			DESCRIPTION
				"Buffer_overflow/TS error"
		::= { imb2000c01v1Entry 85 }

		-- 1.3.6.1.4.1.10106.3.101291.1.1.87
		imb2000c01v1MalformedPck2 OBJECT-TYPE
			SYNTAX BitFail
			MAX-ACCESS read-only
			STATUS current
			DESCRIPTION
				"Malformed packets"
		::= { imb2000c01v1Entry 87 }

		-- 1.3.6.1.4.1.10106.3.101291.1.1.89
		imb2000c01v1RxFail2 OBJECT-TYPE
			SYNTAX BitFail
			MAX-ACCESS read-only
			STATUS current
			DESCRIPTION
				"RX2 stream fail"
		::= { imb2000c01v1Entry 89 }

		-- 1.3.6.1.4.1.10106.3.101291.1.1.91
		imb2000c01v1Rx2PckRate OBJECT-TYPE
			SYNTAX PacketRate
			MAX-ACCESS read-only
			STATUS current
			DESCRIPTION
				"IP packet rate"
		::= { imb2000c01v1Entry 91 }

		-- 1.3.6.1.4.1.10106.3.101291.1.1.93
		imb2000c01v1Rx2LostIpPk OBJECT-TYPE
			SYNTAX PacketNum
			MAX-ACCESS read-only
			STATUS current
			DESCRIPTION
				"Lost IP packets rate"
		::= { imb2000c01v1Entry 93 }

		-- 1.3.6.1.4.1.10106.3.101291.1.1.95
		imb2000c01v1Rx2DupIpPck OBJECT-TYPE
			SYNTAX PacketNum
			MAX-ACCESS read-only
			STATUS current
			DESCRIPTION
				"Duplicated IP packets rate"
		::= { imb2000c01v1Entry 95 }

		-- 1.3.6.1.4.1.10106.3.101291.1.1.97
		imb2000c01v1MaxBuffLev2 OBJECT-TYPE
			SYNTAX BufferPercentag
			MAX-ACCESS read-only
			STATUS current
			DESCRIPTION
				"Maximum buffer level"
		::= { imb2000c01v1Entry 97 }

		-- 1.3.6.1.4.1.10106.3.101291.1.1.99
		imb2000c01v1MinBuffLev2 OBJECT-TYPE
			SYNTAX BufferPercentag
			MAX-ACCESS read-only
			STATUS current
			DESCRIPTION
				"Minimum buffer level"
		::= { imb2000c01v1Entry 99 }

		-- 1.3.6.1.4.1.10106.3.101291.1.1.101
		imb2000c01v1StreamOk3 OBJECT-TYPE
			SYNTAX BitFailN
			MAX-ACCESS read-only
			STATUS current
			DESCRIPTION
				"AES67 stream 3 received"
		::= { imb2000c01v1Entry 101 }

		-- 1.3.6.1.4.1.10106.3.101291.1.1.103
		imb2000c01v1BufferUnderf3 OBJECT-TYPE
			SYNTAX BitFail
			MAX-ACCESS read-only
			STATUS current
			DESCRIPTION
				"Buffer underflow"
		::= { imb2000c01v1Entry 103 }

		-- 1.3.6.1.4.1.10106.3.101291.1.1.105
		imb2000c01v1BufferOverf3 OBJECT-TYPE
			SYNTAX BitFail
			MAX-ACCESS read-only
			STATUS current
			DESCRIPTION
				"Buffer_overflow/TS error"
		::= { imb2000c01v1Entry 105 }

		-- 1.3.6.1.4.1.10106.3.101291.1.1.107
		imb2000c01v1MalformedPck3 OBJECT-TYPE
			SYNTAX BitFail
			MAX-ACCESS read-only
			STATUS current
			DESCRIPTION
				"Malformed packets"
		::= { imb2000c01v1Entry 107 }

		-- 1.3.6.1.4.1.10106.3.101291.1.1.109
		imb2000c01v1RxFail3 OBJECT-TYPE
			SYNTAX BitFail
			MAX-ACCESS read-only
			STATUS current
			DESCRIPTION
				"RX3 stream fail"
		::= { imb2000c01v1Entry 109 }

		-- 1.3.6.1.4.1.10106.3.101291.1.1.111
		imb2000c01v1Rx3PckRate OBJECT-TYPE
			SYNTAX PacketRate
			MAX-ACCESS read-only
			STATUS current
			DESCRIPTION
				"IP packet rate"
		::= { imb2000c01v1Entry 111 }

		-- 1.3.6.1.4.1.10106.3.101291.1.1.113
		imb2000c01v1Rx3LostIpPk OBJECT-TYPE
			SYNTAX PacketNum
			MAX-ACCESS read-only
			STATUS current
			DESCRIPTION
				"Lost IP packets rate"
		::= { imb2000c01v1Entry 113 }

		-- 1.3.6.1.4.1.10106.3.101291.1.1.115
		imb2000c01v1Rx3DupIpPck OBJECT-TYPE
			SYNTAX PacketNum
			MAX-ACCESS read-only
			STATUS current
			DESCRIPTION
				"Duplicated IP packets rate"
		::= { imb2000c01v1Entry 115 }

		-- 1.3.6.1.4.1.10106.3.101291.1.1.117
		imb2000c01v1MaxBuffLev3 OBJECT-TYPE
			SYNTAX BufferPercentag
			MAX-ACCESS read-only
			STATUS current
			DESCRIPTION
				"Maximum buffer level"
		::= { imb2000c01v1Entry 117 }

		-- 1.3.6.1.4.1.10106.3.101291.1.1.119
		imb2000c01v1MinBuffLev3 OBJECT-TYPE
			SYNTAX BufferPercentag
			MAX-ACCESS read-only
			STATUS current
			DESCRIPTION
				"Minimum buffer level"
		::= { imb2000c01v1Entry 119 }

		-- 1.3.6.1.4.1.10106.3.101291.1.1.121
		imb2000c01v1StreamOk4 OBJECT-TYPE
			SYNTAX BitFailN
			MAX-ACCESS read-only
			STATUS current
			DESCRIPTION
				"AES67 stream 4 received"
		::= { imb2000c01v1Entry 121 }

		-- 1.3.6.1.4.1.10106.3.101291.1.1.123
		imb2000c01v1BufferUnderf4 OBJECT-TYPE
			SYNTAX BitFail
			MAX-ACCESS read-only
			STATUS current
			DESCRIPTION
				"Buffer underflow"
		::= { imb2000c01v1Entry 123 }

		-- 1.3.6.1.4.1.10106.3.101291.1.1.125
		imb2000c01v1BufferOverf4 OBJECT-TYPE
			SYNTAX BitFail
			MAX-ACCESS read-only
			STATUS current
			DESCRIPTION
				"Buffer_overflow/TS error"
		::= { imb2000c01v1Entry 125 }

		-- 1.3.6.1.4.1.10106.3.101291.1.1.127
		imb2000c01v1MalformedPck4 OBJECT-TYPE
			SYNTAX BitFail
			MAX-ACCESS read-only
			STATUS current
			DESCRIPTION
				"Malformed packets"
		::= { imb2000c01v1Entry 127 }

		-- 1.3.6.1.4.1.10106.3.101291.1.1.129
		imb2000c01v1RxFail4 OBJECT-TYPE
			SYNTAX BitFail
			MAX-ACCESS read-only
			STATUS current
			DESCRIPTION
				"RX4 stream fail"
		::= { imb2000c01v1Entry 129 }

		-- 1.3.6.1.4.1.10106.3.101291.1.1.131
		imb2000c01v1Rx4PckRate OBJECT-TYPE
			SYNTAX PacketRate
			MAX-ACCESS read-only
			STATUS current
			DESCRIPTION
				"IP packet rate"
		::= { imb2000c01v1Entry 131 }

		-- 1.3.6.1.4.1.10106.3.101291.1.1.133
		imb2000c01v1Rx4LostIpPk OBJECT-TYPE
			SYNTAX PacketNum
			MAX-ACCESS read-only
			STATUS current
			DESCRIPTION
				"Lost IP packets rate"
		::= { imb2000c01v1Entry 133 }

		-- 1.3.6.1.4.1.10106.3.101291.1.1.135
		imb2000c01v1Rx4DupIpPck OBJECT-TYPE
			SYNTAX PacketNum
			MAX-ACCESS read-only
			STATUS current
			DESCRIPTION
				"Duplicated IP packets rate"
		::= { imb2000c01v1Entry 135 }

		-- 1.3.6.1.4.1.10106.3.101291.1.1.137
		imb2000c01v1MaxBuffLev4 OBJECT-TYPE
			SYNTAX BufferPercentag
			MAX-ACCESS read-only
			STATUS current
			DESCRIPTION
				"Maximum buffer level"
		::= { imb2000c01v1Entry 137 }

		-- 1.3.6.1.4.1.10106.3.101291.1.1.139
		imb2000c01v1MinBuffLev4 OBJECT-TYPE
			SYNTAX BufferPercentag
			MAX-ACCESS read-only
			STATUS current
			DESCRIPTION
				"Minimum buffer level"
		::= { imb2000c01v1Entry 139 }

		-- 1.3.6.1.4.1.10106.3.101291.1.1.141
		imb2000c01v1StreamOk5 OBJECT-TYPE
			SYNTAX BitFailN
			MAX-ACCESS read-only
			STATUS current
			DESCRIPTION
				"AES67 stream 5 received"
		::= { imb2000c01v1Entry 141 }

		-- 1.3.6.1.4.1.10106.3.101291.1.1.143
		imb2000c01v1BufferUnderf5 OBJECT-TYPE
			SYNTAX BitFail
			MAX-ACCESS read-only
			STATUS current
			DESCRIPTION
				"Buffer underflow"
		::= { imb2000c01v1Entry 143 }

		-- 1.3.6.1.4.1.10106.3.101291.1.1.145
		imb2000c01v1BufferOverf5 OBJECT-TYPE
			SYNTAX BitFail
			MAX-ACCESS read-only
			STATUS current
			DESCRIPTION
				"Buffer_overflow/TS error"
		::= { imb2000c01v1Entry 145 }

		-- 1.3.6.1.4.1.10106.3.101291.1.1.147
		imb2000c01v1MalformedPck5 OBJECT-TYPE
			SYNTAX BitFail
			MAX-ACCESS read-only
			STATUS current
			DESCRIPTION
				"Malformed packets"
		::= { imb2000c01v1Entry 147 }

		-- 1.3.6.1.4.1.10106.3.101291.1.1.149
		imb2000c01v1RxFail5 OBJECT-TYPE
			SYNTAX BitFail
			MAX-ACCESS read-only
			STATUS current
			DESCRIPTION
				"RX5 stream fail"
		::= { imb2000c01v1Entry 149 }

		-- 1.3.6.1.4.1.10106.3.101291.1.1.151
		imb2000c01v1Rx5PckRate OBJECT-TYPE
			SYNTAX PacketRate
			MAX-ACCESS read-only
			STATUS current
			DESCRIPTION
				"IP packet rate"
		::= { imb2000c01v1Entry 151 }

		-- 1.3.6.1.4.1.10106.3.101291.1.1.153
		imb2000c01v1Rx5LostIpPk OBJECT-TYPE
			SYNTAX PacketNum
			MAX-ACCESS read-only
			STATUS current
			DESCRIPTION
				"Lost IP packets rate"
		::= { imb2000c01v1Entry 153 }

		-- 1.3.6.1.4.1.10106.3.101291.1.1.155
		imb2000c01v1Rx5DupIpPck OBJECT-TYPE
			SYNTAX PacketNum
			MAX-ACCESS read-only
			STATUS current
			DESCRIPTION
				"Duplicated IP packets rate"
		::= { imb2000c01v1Entry 155 }

		-- 1.3.6.1.4.1.10106.3.101291.1.1.157
		imb2000c01v1MaxBuffLev5 OBJECT-TYPE
			SYNTAX BufferPercentag
			MAX-ACCESS read-only
			STATUS current
			DESCRIPTION
				"Maximum buffer level"
		::= { imb2000c01v1Entry 157 }

		-- 1.3.6.1.4.1.10106.3.101291.1.1.159
		imb2000c01v1MinBuffLev5 OBJECT-TYPE
			SYNTAX BufferPercentag
			MAX-ACCESS read-only
			STATUS current
			DESCRIPTION
				"Minimum buffer level"
		::= { imb2000c01v1Entry 159 }

		-- 1.3.6.1.4.1.10106.3.101291.1.1.161
		imb2000c01v1StreamOk6 OBJECT-TYPE
			SYNTAX BitFailN
			MAX-ACCESS read-only
			STATUS current
			DESCRIPTION
				"AES67 stream 6 received"
		::= { imb2000c01v1Entry 161 }

		-- 1.3.6.1.4.1.10106.3.101291.1.1.163
		imb2000c01v1BufferUnderf6 OBJECT-TYPE
			SYNTAX BitFail
			MAX-ACCESS read-only
			STATUS current
			DESCRIPTION
				"Buffer underflow"
		::= { imb2000c01v1Entry 163 }

		-- 1.3.6.1.4.1.10106.3.101291.1.1.165
		imb2000c01v1BufferOverf6 OBJECT-TYPE
			SYNTAX BitFail
			MAX-ACCESS read-only
			STATUS current
			DESCRIPTION
				"Buffer_overflow/TS error"
		::= { imb2000c01v1Entry 165 }

		-- 1.3.6.1.4.1.10106.3.101291.1.1.167
		imb2000c01v1MalformedPck6 OBJECT-TYPE
			SYNTAX BitFail
			MAX-ACCESS read-only
			STATUS current
			DESCRIPTION
				"Malformed packets"
		::= { imb2000c01v1Entry 167 }

		-- 1.3.6.1.4.1.10106.3.101291.1.1.169
		imb2000c01v1RxFail6 OBJECT-TYPE
			SYNTAX BitFail
			MAX-ACCESS read-only
			STATUS current
			DESCRIPTION
				"RX6 stream fail"
		::= { imb2000c01v1Entry 169 }

		-- 1.3.6.1.4.1.10106.3.101291.1.1.171
		imb2000c01v1Rx6PckRate OBJECT-TYPE
			SYNTAX PacketRate
			MAX-ACCESS read-only
			STATUS current
			DESCRIPTION
				"IP packet rate"
		::= { imb2000c01v1Entry 171 }

		-- 1.3.6.1.4.1.10106.3.101291.1.1.173
		imb2000c01v1Rx6LostIpPk OBJECT-TYPE
			SYNTAX PacketNum
			MAX-ACCESS read-only
			STATUS current
			DESCRIPTION
				"Lost IP packets rate"
		::= { imb2000c01v1Entry 173 }

		-- 1.3.6.1.4.1.10106.3.101291.1.1.175
		imb2000c01v1Rx6DupIpPck OBJECT-TYPE
			SYNTAX PacketNum
			MAX-ACCESS read-only
			STATUS current
			DESCRIPTION
				"Duplicated IP packets rate"
		::= { imb2000c01v1Entry 175 }

		-- 1.3.6.1.4.1.10106.3.101291.1.1.177
		imb2000c01v1MaxBuffLev6 OBJECT-TYPE
			SYNTAX BufferPercentag
			MAX-ACCESS read-only
			STATUS current
			DESCRIPTION
				"Maximum buffer level"
		::= { imb2000c01v1Entry 177 }

		-- 1.3.6.1.4.1.10106.3.101291.1.1.179
		imb2000c01v1MinBuffLev6 OBJECT-TYPE
			SYNTAX BufferPercentag
			MAX-ACCESS read-only
			STATUS current
			DESCRIPTION
				"Minimum buffer level"
		::= { imb2000c01v1Entry 179 }

		-- 1.3.6.1.4.1.10106.3.101291.1.1.181
		imb2000c01v1StreamOk7 OBJECT-TYPE
			SYNTAX BitFailN
			MAX-ACCESS read-only
			STATUS current
			DESCRIPTION
				"AES67 stream 7 received"
		::= { imb2000c01v1Entry 181 }

		-- 1.3.6.1.4.1.10106.3.101291.1.1.183
		imb2000c01v1BufferUnderf7 OBJECT-TYPE
			SYNTAX BitFail
			MAX-ACCESS read-only
			STATUS current
			DESCRIPTION
				"Buffer underflow"
		::= { imb2000c01v1Entry 183 }

		-- 1.3.6.1.4.1.10106.3.101291.1.1.185
		imb2000c01v1BufferOverf7 OBJECT-TYPE
			SYNTAX BitFail
			MAX-ACCESS read-only
			STATUS current
			DESCRIPTION
				"Buffer_overflow/TS error"
		::= { imb2000c01v1Entry 185 }

		-- 1.3.6.1.4.1.10106.3.101291.1.1.187
		imb2000c01v1MalformedPck7 OBJECT-TYPE
			SYNTAX BitFail
			MAX-ACCESS read-only
			STATUS current
			DESCRIPTION
				"Malformed packets"
		::= { imb2000c01v1Entry 187 }

		-- 1.3.6.1.4.1.10106.3.101291.1.1.189
		imb2000c01v1RxFail7 OBJECT-TYPE
			SYNTAX BitFail
			MAX-ACCESS read-only
			STATUS current
			DESCRIPTION
				"RX7 stream fail"
		::= { imb2000c01v1Entry 189 }

		-- 1.3.6.1.4.1.10106.3.101291.1.1.191
		imb2000c01v1Rx7PckRate OBJECT-TYPE
			SYNTAX PacketRate
			MAX-ACCESS read-only
			STATUS current
			DESCRIPTION
				"IP packet rate"
		::= { imb2000c01v1Entry 191 }

		-- 1.3.6.1.4.1.10106.3.101291.1.1.193
		imb2000c01v1Rx7LostIpPk OBJECT-TYPE
			SYNTAX PacketNum
			MAX-ACCESS read-only
			STATUS current
			DESCRIPTION
				"Lost IP packets rate"
		::= { imb2000c01v1Entry 193 }

		-- 1.3.6.1.4.1.10106.3.101291.1.1.195
		imb2000c01v1Rx7DupIpPck OBJECT-TYPE
			SYNTAX PacketNum
			MAX-ACCESS read-only
			STATUS current
			DESCRIPTION
				"Duplicated IP packets rate"
		::= { imb2000c01v1Entry 195 }

		-- 1.3.6.1.4.1.10106.3.101291.1.1.197
		imb2000c01v1MaxBuffLev7 OBJECT-TYPE
			SYNTAX BufferPercentag
			MAX-ACCESS read-only
			STATUS current
			DESCRIPTION
				"Maximum buffer level"
		::= { imb2000c01v1Entry 197 }

		-- 1.3.6.1.4.1.10106.3.101291.1.1.199
		imb2000c01v1MinBuffLev7 OBJECT-TYPE
			SYNTAX BufferPercentag
			MAX-ACCESS read-only
			STATUS current
			DESCRIPTION
				"Minimum buffer level"
		::= { imb2000c01v1Entry 199 }

		-- 1.3.6.1.4.1.10106.3.101291.1.1.201
		imb2000c01v1StreamOk8 OBJECT-TYPE
			SYNTAX BitFailN
			MAX-ACCESS read-only
			STATUS current
			DESCRIPTION
				"AES67 stream 8 received"
		::= { imb2000c01v1Entry 201 }

		-- 1.3.6.1.4.1.10106.3.101291.1.1.203
		imb2000c01v1BufferUnderf8 OBJECT-TYPE
			SYNTAX BitFail
			MAX-ACCESS read-only
			STATUS current
			DESCRIPTION
				"Buffer underflow"
		::= { imb2000c01v1Entry 203 }

		-- 1.3.6.1.4.1.10106.3.101291.1.1.205
		imb2000c01v1BufferOverf8 OBJECT-TYPE
			SYNTAX BitFail
			MAX-ACCESS read-only
			STATUS current
			DESCRIPTION
				"Buffer_overflow/TS error"
		::= { imb2000c01v1Entry 205 }

		-- 1.3.6.1.4.1.10106.3.101291.1.1.207
		imb2000c01v1MalformedPck8 OBJECT-TYPE
			SYNTAX BitFail
			MAX-ACCESS read-only
			STATUS current
			DESCRIPTION
				"Malformed packets"
		::= { imb2000c01v1Entry 207 }

		-- 1.3.6.1.4.1.10106.3.101291.1.1.209
		imb2000c01v1RxFail8 OBJECT-TYPE
			SYNTAX BitFail
			MAX-ACCESS read-only
			STATUS current
			DESCRIPTION
				"RX8 stream fail"
		::= { imb2000c01v1Entry 209 }

		-- 1.3.6.1.4.1.10106.3.101291.1.1.211
		imb2000c01v1Rx8PckRate OBJECT-TYPE
			SYNTAX PacketRate
			MAX-ACCESS read-only
			STATUS current
			DESCRIPTION
				"IP packet rate"
		::= { imb2000c01v1Entry 211 }

		-- 1.3.6.1.4.1.10106.3.101291.1.1.213
		imb2000c01v1Rx8LostIpPk OBJECT-TYPE
			SYNTAX PacketNum
			MAX-ACCESS read-only
			STATUS current
			DESCRIPTION
				"Lost IP packets rate"
		::= { imb2000c01v1Entry 213 }

		-- 1.3.6.1.4.1.10106.3.101291.1.1.215
		imb2000c01v1Rx8DupIpPck OBJECT-TYPE
			SYNTAX PacketNum
			MAX-ACCESS read-only
			STATUS current
			DESCRIPTION
				"Duplicated IP packets rate"
		::= { imb2000c01v1Entry 215 }

		-- 1.3.6.1.4.1.10106.3.101291.1.1.217
		imb2000c01v1MaxBuffLev8 OBJECT-TYPE
			SYNTAX BufferPercentag
			MAX-ACCESS read-only
			STATUS current
			DESCRIPTION
				"Maximum buffer level"
		::= { imb2000c01v1Entry 217 }

		-- 1.3.6.1.4.1.10106.3.101291.1.1.219
		imb2000c01v1MinBuffLev8 OBJECT-TYPE
			SYNTAX BufferPercentag
			MAX-ACCESS read-only
			STATUS current
			DESCRIPTION
				"Minimum buffer level"
		::= { imb2000c01v1Entry 219 }

		-- 1.3.6.1.4.1.10106.3.101291.1.1.221
		imb2000c01v1StreamOk9 OBJECT-TYPE
			SYNTAX BitFailN
			MAX-ACCESS read-only
			STATUS current
			DESCRIPTION
				"AES67 stream 9 received"
		::= { imb2000c01v1Entry 221 }

		-- 1.3.6.1.4.1.10106.3.101291.1.1.223
		imb2000c01v1BufferUnderf9 OBJECT-TYPE
			SYNTAX BitFail
			MAX-ACCESS read-only
			STATUS current
			DESCRIPTION
				"Buffer underflow"
		::= { imb2000c01v1Entry 223 }

		-- 1.3.6.1.4.1.10106.3.101291.1.1.225
		imb2000c01v1BufferOverf9 OBJECT-TYPE
			SYNTAX BitFail
			MAX-ACCESS read-only
			STATUS current
			DESCRIPTION
				"Buffer_overflow/TS error"
		::= { imb2000c01v1Entry 225 }

		-- 1.3.6.1.4.1.10106.3.101291.1.1.227
		imb2000c01v1MalformedPck9 OBJECT-TYPE
			SYNTAX BitFail
			MAX-ACCESS read-only
			STATUS current
			DESCRIPTION
				"Malformed packets"
		::= { imb2000c01v1Entry 227 }

		-- 1.3.6.1.4.1.10106.3.101291.1.1.229
		imb2000c01v1RxFail9 OBJECT-TYPE
			SYNTAX BitFail
			MAX-ACCESS read-only
			STATUS current
			DESCRIPTION
				"RX9 stream fail"
		::= { imb2000c01v1Entry 229 }

		-- 1.3.6.1.4.1.10106.3.101291.1.1.231
		imb2000c01v1Rx9PckRate OBJECT-TYPE
			SYNTAX PacketRate
			MAX-ACCESS read-only
			STATUS current
			DESCRIPTION
				"IP packet rate"
		::= { imb2000c01v1Entry 231 }

		-- 1.3.6.1.4.1.10106.3.101291.1.1.233
		imb2000c01v1Rx9LostIpPk OBJECT-TYPE
			SYNTAX PacketNum
			MAX-ACCESS read-only
			STATUS current
			DESCRIPTION
				"Lost IP packets rate"
		::= { imb2000c01v1Entry 233 }

		-- 1.3.6.1.4.1.10106.3.101291.1.1.235
		imb2000c01v1Rx9DupIpPck OBJECT-TYPE
			SYNTAX PacketNum
			MAX-ACCESS read-only
			STATUS current
			DESCRIPTION
				"Duplicated IP packets rate"
		::= { imb2000c01v1Entry 235 }

		-- 1.3.6.1.4.1.10106.3.101291.1.1.237
		imb2000c01v1MaxBuffLev9 OBJECT-TYPE
			SYNTAX BufferPercentag
			MAX-ACCESS read-only
			STATUS current
			DESCRIPTION
				"Maximum buffer level"
		::= { imb2000c01v1Entry 237 }

		-- 1.3.6.1.4.1.10106.3.101291.1.1.239
		imb2000c01v1MinBuffLev9 OBJECT-TYPE
			SYNTAX BufferPercentag
			MAX-ACCESS read-only
			STATUS current
			DESCRIPTION
				"Minimum buffer level"
		::= { imb2000c01v1Entry 239 }

		-- 1.3.6.1.4.1.10106.3.101291.1.1.241
		imb2000c01v1StreamOk10 OBJECT-TYPE
			SYNTAX BitFailN
			MAX-ACCESS read-only
			STATUS current
			DESCRIPTION
				"AES67 stream 10 received"
		::= { imb2000c01v1Entry 241 }

		-- 1.3.6.1.4.1.10106.3.101291.1.1.243
		imb2000c01v1BufferUnderf10 OBJECT-TYPE
			SYNTAX BitFail
			MAX-ACCESS read-only
			STATUS current
			DESCRIPTION
				"Buffer underflow"
		::= { imb2000c01v1Entry 243 }

		-- 1.3.6.1.4.1.10106.3.101291.1.1.245
		imb2000c01v1BufferOverf10 OBJECT-TYPE
			SYNTAX BitFail
			MAX-ACCESS read-only
			STATUS current
			DESCRIPTION
				"Buffer_overflow/TS error"
		::= { imb2000c01v1Entry 245 }

		-- 1.3.6.1.4.1.10106.3.101291.1.1.247
		imb2000c01v1MalformedPck10 OBJECT-TYPE
			SYNTAX BitFail
			MAX-ACCESS read-only
			STATUS current
			DESCRIPTION
				"Malformed packets"
		::= { imb2000c01v1Entry 247 }

		-- 1.3.6.1.4.1.10106.3.101291.1.1.249
		imb2000c01v1RxFail10 OBJECT-TYPE
			SYNTAX BitFail
			MAX-ACCESS read-only
			STATUS current
			DESCRIPTION
				"RX10 stream fail"
		::= { imb2000c01v1Entry 249 }

		-- 1.3.6.1.4.1.10106.3.101291.1.1.251
		imb2000c01v1Rx10PckRate OBJECT-TYPE
			SYNTAX PacketRate
			MAX-ACCESS read-only
			STATUS current
			DESCRIPTION
				"IP packet rate"
		::= { imb2000c01v1Entry 251 }

		-- 1.3.6.1.4.1.10106.3.101291.1.1.253
		imb2000c01v1Rx10LostIpPk OBJECT-TYPE
			SYNTAX PacketNum
			MAX-ACCESS read-only
			STATUS current
			DESCRIPTION
				"Lost IP packets rate"
		::= { imb2000c01v1Entry 253 }

		-- 1.3.6.1.4.1.10106.3.101291.1.1.255
		imb2000c01v1Rx10DupIpPck OBJECT-TYPE
			SYNTAX PacketNum
			MAX-ACCESS read-only
			STATUS current
			DESCRIPTION
				"Duplicated IP packets rate"
		::= { imb2000c01v1Entry 255 }

		-- 1.3.6.1.4.1.10106.3.101291.1.1.257
		imb2000c01v1MaxBuffLev10 OBJECT-TYPE
			SYNTAX BufferPercentag
			MAX-ACCESS read-only
			STATUS current
			DESCRIPTION
				"Maximum buffer level"
		::= { imb2000c01v1Entry 257 }

		-- 1.3.6.1.4.1.10106.3.101291.1.1.259
		imb2000c01v1MinBuffLev10 OBJECT-TYPE
			SYNTAX BufferPercentag
			MAX-ACCESS read-only
			STATUS current
			DESCRIPTION
				"Minimum buffer level"
		::= { imb2000c01v1Entry 259 }

		-- 1.3.6.1.4.1.10106.3.101291.1.1.261
		imb2000c01v1StreamOk11 OBJECT-TYPE
			SYNTAX BitFailN
			MAX-ACCESS read-only
			STATUS current
			DESCRIPTION
				"AES67 stream 11 received"
		::= { imb2000c01v1Entry 261 }

		-- 1.3.6.1.4.1.10106.3.101291.1.1.263
		imb2000c01v1BufferUnderf11 OBJECT-TYPE
			SYNTAX BitFail
			MAX-ACCESS read-only
			STATUS current
			DESCRIPTION
				"Buffer underflow"
		::= { imb2000c01v1Entry 263 }

		-- 1.3.6.1.4.1.10106.3.101291.1.1.265
		imb2000c01v1BufferOverf11 OBJECT-TYPE
			SYNTAX BitFail
			MAX-ACCESS read-only
			STATUS current
			DESCRIPTION
				"Buffer_overflow/TS error"
		::= { imb2000c01v1Entry 265 }

		-- 1.3.6.1.4.1.10106.3.101291.1.1.267
		imb2000c01v1MalformedPck11 OBJECT-TYPE
			SYNTAX BitFail
			MAX-ACCESS read-only
			STATUS current
			DESCRIPTION
				"Malformed packets"
		::= { imb2000c01v1Entry 267 }

		-- 1.3.6.1.4.1.10106.3.101291.1.1.269
		imb2000c01v1RxFail11 OBJECT-TYPE
			SYNTAX BitFail
			MAX-ACCESS read-only
			STATUS current
			DESCRIPTION
				"RX11 stream fail"
		::= { imb2000c01v1Entry 269 }

		-- 1.3.6.1.4.1.10106.3.101291.1.1.271
		imb2000c01v1Rx11PckRate OBJECT-TYPE
			SYNTAX PacketRate
			MAX-ACCESS read-only
			STATUS current
			DESCRIPTION
				"IP packet rate"
		::= { imb2000c01v1Entry 271 }

		-- 1.3.6.1.4.1.10106.3.101291.1.1.273
		imb2000c01v1Rx11LostIpPk OBJECT-TYPE
			SYNTAX PacketNum
			MAX-ACCESS read-only
			STATUS current
			DESCRIPTION
				"Lost IP packets rate"
		::= { imb2000c01v1Entry 273 }

		-- 1.3.6.1.4.1.10106.3.101291.1.1.275
		imb2000c01v1Rx11DupIpPck OBJECT-TYPE
			SYNTAX PacketNum
			MAX-ACCESS read-only
			STATUS current
			DESCRIPTION
				"Duplicated IP packets rate"
		::= { imb2000c01v1Entry 275 }

		-- 1.3.6.1.4.1.10106.3.101291.1.1.277
		imb2000c01v1MaxBuffLev11 OBJECT-TYPE
			SYNTAX BufferPercentag
			MAX-ACCESS read-only
			STATUS current
			DESCRIPTION
				"Maximum buffer level"
		::= { imb2000c01v1Entry 277 }

		-- 1.3.6.1.4.1.10106.3.101291.1.1.279
		imb2000c01v1MinBuffLev11 OBJECT-TYPE
			SYNTAX BufferPercentag
			MAX-ACCESS read-only
			STATUS current
			DESCRIPTION
				"Minimum buffer level"
		::= { imb2000c01v1Entry 279 }

		-- 1.3.6.1.4.1.10106.3.101291.1.1.281
		imb2000c01v1StreamOk12 OBJECT-TYPE
			SYNTAX BitFailN
			MAX-ACCESS read-only
			STATUS current
			DESCRIPTION
				"AES67 stream 12 received"
		::= { imb2000c01v1Entry 281 }

		-- 1.3.6.1.4.1.10106.3.101291.1.1.283
		imb2000c01v1BufferUnderf12 OBJECT-TYPE
			SYNTAX BitFail
			MAX-ACCESS read-only
			STATUS current
			DESCRIPTION
				"Buffer underflow"
		::= { imb2000c01v1Entry 283 }

		-- 1.3.6.1.4.1.10106.3.101291.1.1.285
		imb2000c01v1BufferOverf12 OBJECT-TYPE
			SYNTAX BitFail
			MAX-ACCESS read-only
			STATUS current
			DESCRIPTION
				"Buffer_overflow/TS error"
		::= { imb2000c01v1Entry 285 }

		-- 1.3.6.1.4.1.10106.3.101291.1.1.287
		imb2000c01v1MalformedPck12 OBJECT-TYPE
			SYNTAX BitFail
			MAX-ACCESS read-only
			STATUS current
			DESCRIPTION
				"Malformed packets"
		::= { imb2000c01v1Entry 287 }

		-- 1.3.6.1.4.1.10106.3.101291.1.1.289
		imb2000c01v1RxFail12 OBJECT-TYPE
			SYNTAX BitFail
			MAX-ACCESS read-only
			STATUS current
			DESCRIPTION
				"RX12 stream fail"
		::= { imb2000c01v1Entry 289 }

		-- 1.3.6.1.4.1.10106.3.101291.1.1.291
		imb2000c01v1Rx12PckRate OBJECT-TYPE
			SYNTAX PacketRate
			MAX-ACCESS read-only
			STATUS current
			DESCRIPTION
				"IP packet rate"
		::= { imb2000c01v1Entry 291 }

		-- 1.3.6.1.4.1.10106.3.101291.1.1.293
		imb2000c01v1Rx12LostIpPk OBJECT-TYPE
			SYNTAX PacketNum
			MAX-ACCESS read-only
			STATUS current
			DESCRIPTION
				"Lost IP packets rate"
		::= { imb2000c01v1Entry 293 }

		-- 1.3.6.1.4.1.10106.3.101291.1.1.295
		imb2000c01v1Rx12DupIpPck OBJECT-TYPE
			SYNTAX PacketNum
			MAX-ACCESS read-only
			STATUS current
			DESCRIPTION
				"Duplicated IP packets rate"
		::= { imb2000c01v1Entry 295 }

		-- 1.3.6.1.4.1.10106.3.101291.1.1.297
		imb2000c01v1MaxBuffLev12 OBJECT-TYPE
			SYNTAX BufferPercentag
			MAX-ACCESS read-only
			STATUS current
			DESCRIPTION
				"Maximum buffer level"
		::= { imb2000c01v1Entry 297 }

		-- 1.3.6.1.4.1.10106.3.101291.1.1.299
		imb2000c01v1MinBuffLev12 OBJECT-TYPE
			SYNTAX BufferPercentag
			MAX-ACCESS read-only
			STATUS current
			DESCRIPTION
				"Minimum buffer level"
		::= { imb2000c01v1Entry 299 }

		-- 1.3.6.1.4.1.10106.3.101291.1.1.301
		imb2000c01v1StreamOk13 OBJECT-TYPE
			SYNTAX BitFailN
			MAX-ACCESS read-only
			STATUS current
			DESCRIPTION
				"AES67 stream 13 received"
		::= { imb2000c01v1Entry 301 }

		-- 1.3.6.1.4.1.10106.3.101291.1.1.303
		imb2000c01v1BufferUnderf13 OBJECT-TYPE
			SYNTAX BitFail
			MAX-ACCESS read-only
			STATUS current
			DESCRIPTION
				"Buffer underflow"
		::= { imb2000c01v1Entry 303 }

		-- 1.3.6.1.4.1.10106.3.101291.1.1.305
		imb2000c01v1BufferOverf13 OBJECT-TYPE
			SYNTAX BitFail
			MAX-ACCESS read-only
			STATUS current
			DESCRIPTION
				"Buffer_overflow/TS error"
		::= { imb2000c01v1Entry 305 }

		-- 1.3.6.1.4.1.10106.3.101291.1.1.307
		imb2000c01v1MalformedPck13 OBJECT-TYPE
			SYNTAX BitFail
			MAX-ACCESS read-only
			STATUS current
			DESCRIPTION
				"Malformed packets"
		::= { imb2000c01v1Entry 307 }

		-- 1.3.6.1.4.1.10106.3.101291.1.1.309
		imb2000c01v1RxFail13 OBJECT-TYPE
			SYNTAX BitFail
			MAX-ACCESS read-only
			STATUS current
			DESCRIPTION
				"RX13 stream fail"
		::= { imb2000c01v1Entry 309 }

		-- 1.3.6.1.4.1.10106.3.101291.1.1.311
		imb2000c01v1Rx13PckRate OBJECT-TYPE
			SYNTAX PacketRate
			MAX-ACCESS read-only
			STATUS current
			DESCRIPTION
				"IP packet rate"
		::= { imb2000c01v1Entry 311 }

		-- 1.3.6.1.4.1.10106.3.101291.1.1.313
		imb2000c01v1Rx13LostIpPk OBJECT-TYPE
			SYNTAX PacketNum
			MAX-ACCESS read-only
			STATUS current
			DESCRIPTION
				"Lost IP packets rate"
		::= { imb2000c01v1Entry 313 }

		-- 1.3.6.1.4.1.10106.3.101291.1.1.315
		imb2000c01v1Rx13DupIpPck OBJECT-TYPE
			SYNTAX PacketNum
			MAX-ACCESS read-only
			STATUS current
			DESCRIPTION
				"Duplicated IP packets rate"
		::= { imb2000c01v1Entry 315 }

		-- 1.3.6.1.4.1.10106.3.101291.1.1.317
		imb2000c01v1MaxBuffLev13 OBJECT-TYPE
			SYNTAX BufferPercentag
			MAX-ACCESS read-only
			STATUS current
			DESCRIPTION
				"Maximum buffer level"
		::= { imb2000c01v1Entry 317 }

		-- 1.3.6.1.4.1.10106.3.101291.1.1.319
		imb2000c01v1MinBuffLev13 OBJECT-TYPE
			SYNTAX BufferPercentag
			MAX-ACCESS read-only
			STATUS current
			DESCRIPTION
				"Minimum buffer level"
		::= { imb2000c01v1Entry 319 }

		-- 1.3.6.1.4.1.10106.3.101291.1.1.321
		imb2000c01v1StreamOk14 OBJECT-TYPE
			SYNTAX BitFailN
			MAX-ACCESS read-only
			STATUS current
			DESCRIPTION
				"AES67 stream 14 received"
		::= { imb2000c01v1Entry 321 }

		-- 1.3.6.1.4.1.10106.3.101291.1.1.323
		imb2000c01v1BufferUnderf14 OBJECT-TYPE
			SYNTAX BitFail
			MAX-ACCESS read-only
			STATUS current
			DESCRIPTION
				"Buffer underflow"
		::= { imb2000c01v1Entry 323 }

		-- 1.3.6.1.4.1.10106.3.101291.1.1.325
		imb2000c01v1BufferOverf14 OBJECT-TYPE
			SYNTAX BitFail
			MAX-ACCESS read-only
			STATUS current
			DESCRIPTION
				"Buffer_overflow/TS error"
		::= { imb2000c01v1Entry 325 }

		-- 1.3.6.1.4.1.10106.3.101291.1.1.327
		imb2000c01v1MalformedPck14 OBJECT-TYPE
			SYNTAX BitFail
			MAX-ACCESS read-only
			STATUS current
			DESCRIPTION
				"Malformed packets"
		::= { imb2000c01v1Entry 327 }

		-- 1.3.6.1.4.1.10106.3.101291.1.1.329
		imb2000c01v1RxFail14 OBJECT-TYPE
			SYNTAX BitFail
			MAX-ACCESS read-only
			STATUS current
			DESCRIPTION
				"RX14 stream fail"
		::= { imb2000c01v1Entry 329 }

		-- 1.3.6.1.4.1.10106.3.101291.1.1.331
		imb2000c01v1Rx14PckRate OBJECT-TYPE
			SYNTAX PacketRate
			MAX-ACCESS read-only
			STATUS current
			DESCRIPTION
				"IP packet rate"
		::= { imb2000c01v1Entry 331 }

		-- 1.3.6.1.4.1.10106.3.101291.1.1.333
		imb2000c01v1Rx14LostIpPk OBJECT-TYPE
			SYNTAX PacketNum
			MAX-ACCESS read-only
			STATUS current
			DESCRIPTION
				"Lost IP packets rate"
		::= { imb2000c01v1Entry 333 }

		-- 1.3.6.1.4.1.10106.3.101291.1.1.335
		imb2000c01v1Rx14DupIpPck OBJECT-TYPE
			SYNTAX PacketNum
			MAX-ACCESS read-only
			STATUS current
			DESCRIPTION
				"Duplicated IP packets rate"
		::= { imb2000c01v1Entry 335 }

		-- 1.3.6.1.4.1.10106.3.101291.1.1.337
		imb2000c01v1MaxBuffLev14 OBJECT-TYPE
			SYNTAX BufferPercentag
			MAX-ACCESS read-only
			STATUS current
			DESCRIPTION
				"Maximum buffer level"
		::= { imb2000c01v1Entry 337 }

		-- 1.3.6.1.4.1.10106.3.101291.1.1.339
		imb2000c01v1MinBuffLev14 OBJECT-TYPE
			SYNTAX BufferPercentag
			MAX-ACCESS read-only
			STATUS current
			DESCRIPTION
				"Minimum buffer level"
		::= { imb2000c01v1Entry 339 }

		-- 1.3.6.1.4.1.10106.3.101291.1.1.341
		imb2000c01v1StreamOk15 OBJECT-TYPE
			SYNTAX BitFailN
			MAX-ACCESS read-only
			STATUS current
			DESCRIPTION
				"AES67 stream 15 received"
		::= { imb2000c01v1Entry 341 }

		-- 1.3.6.1.4.1.10106.3.101291.1.1.343
		imb2000c01v1BufferUnderf15 OBJECT-TYPE
			SYNTAX BitFail
			MAX-ACCESS read-only
			STATUS current
			DESCRIPTION
				"Buffer underflow"
		::= { imb2000c01v1Entry 343 }

		-- 1.3.6.1.4.1.10106.3.101291.1.1.345
		imb2000c01v1BufferOverf15 OBJECT-TYPE
			SYNTAX BitFail
			MAX-ACCESS read-only
			STATUS current
			DESCRIPTION
				"Buffer_overflow/TS error"
		::= { imb2000c01v1Entry 345 }

		-- 1.3.6.1.4.1.10106.3.101291.1.1.347
		imb2000c01v1MalformedPck15 OBJECT-TYPE
			SYNTAX BitFail
			MAX-ACCESS read-only
			STATUS current
			DESCRIPTION
				"Malformed packets"
		::= { imb2000c01v1Entry 347 }

		-- 1.3.6.1.4.1.10106.3.101291.1.1.349
		imb2000c01v1RxFail15 OBJECT-TYPE
			SYNTAX BitFail
			MAX-ACCESS read-only
			STATUS current
			DESCRIPTION
				"RX15 stream fail"
		::= { imb2000c01v1Entry 349 }

		-- 1.3.6.1.4.1.10106.3.101291.1.1.351
		imb2000c01v1Rx15PckRate OBJECT-TYPE
			SYNTAX PacketRate
			MAX-ACCESS read-only
			STATUS current
			DESCRIPTION
				"IP packet rate"
		::= { imb2000c01v1Entry 351 }

		-- 1.3.6.1.4.1.10106.3.101291.1.1.353
		imb2000c01v1Rx15LostIpPk OBJECT-TYPE
			SYNTAX PacketNum
			MAX-ACCESS read-only
			STATUS current
			DESCRIPTION
				"Lost IP packets rate"
		::= { imb2000c01v1Entry 353 }

		-- 1.3.6.1.4.1.10106.3.101291.1.1.355
		imb2000c01v1Rx15DupIpPck OBJECT-TYPE
			SYNTAX PacketNum
			MAX-ACCESS read-only
			STATUS current
			DESCRIPTION
				"Duplicated IP packets rate"
		::= { imb2000c01v1Entry 355 }

		-- 1.3.6.1.4.1.10106.3.101291.1.1.357
		imb2000c01v1MaxBuffLev15 OBJECT-TYPE
			SYNTAX BufferPercentag
			MAX-ACCESS read-only
			STATUS current
			DESCRIPTION
				"Maximum buffer level"
		::= { imb2000c01v1Entry 357 }

		-- 1.3.6.1.4.1.10106.3.101291.1.1.359
		imb2000c01v1MinBuffLev15 OBJECT-TYPE
			SYNTAX BufferPercentag
			MAX-ACCESS read-only
			STATUS current
			DESCRIPTION
				"Minimum buffer level"
		::= { imb2000c01v1Entry 359 }

		-- 1.3.6.1.4.1.10106.3.101291.1.1.361
		imb2000c01v1StreamOk16 OBJECT-TYPE
			SYNTAX BitFailN
			MAX-ACCESS read-only
			STATUS current
			DESCRIPTION
				"AES67 stream 16 received"
		::= { imb2000c01v1Entry 361 }

		-- 1.3.6.1.4.1.10106.3.101291.1.1.363
		imb2000c01v1BufferUnderf16 OBJECT-TYPE
			SYNTAX BitFail
			MAX-ACCESS read-only
			STATUS current
			DESCRIPTION
				"Buffer underflow"
		::= { imb2000c01v1Entry 363 }

		-- 1.3.6.1.4.1.10106.3.101291.1.1.365
		imb2000c01v1BufferOverf16 OBJECT-TYPE
			SYNTAX BitFail
			MAX-ACCESS read-only
			STATUS current
			DESCRIPTION
				"Buffer_overflow/TS error"
		::= { imb2000c01v1Entry 365 }

		-- 1.3.6.1.4.1.10106.3.101291.1.1.367
		imb2000c01v1MalformedPck16 OBJECT-TYPE
			SYNTAX BitFail
			MAX-ACCESS read-only
			STATUS current
			DESCRIPTION
				"Malformed packets"
		::= { imb2000c01v1Entry 367 }

		-- 1.3.6.1.4.1.10106.3.101291.1.1.369
		imb2000c01v1RxFail16 OBJECT-TYPE
			SYNTAX BitFail
			MAX-ACCESS read-only
			STATUS current
			DESCRIPTION
				"RX16 stream fail"
		::= { imb2000c01v1Entry 369 }

		-- 1.3.6.1.4.1.10106.3.101291.1.1.371
		imb2000c01v1Rx16PckRate OBJECT-TYPE
			SYNTAX PacketRate
			MAX-ACCESS read-only
			STATUS current
			DESCRIPTION
				"IP packet rate"
		::= { imb2000c01v1Entry 371 }

		-- 1.3.6.1.4.1.10106.3.101291.1.1.373
		imb2000c01v1Rx16LostIpPk OBJECT-TYPE
			SYNTAX PacketNum
			MAX-ACCESS read-only
			STATUS current
			DESCRIPTION
				"Lost IP packets rate"
		::= { imb2000c01v1Entry 373 }

		-- 1.3.6.1.4.1.10106.3.101291.1.1.375
		imb2000c01v1Rx16DupIpPck OBJECT-TYPE
			SYNTAX PacketNum
			MAX-ACCESS read-only
			STATUS current
			DESCRIPTION
				"Duplicated IP packets rate"
		::= { imb2000c01v1Entry 375 }

		-- 1.3.6.1.4.1.10106.3.101291.1.1.377
		imb2000c01v1MaxBuffLev16 OBJECT-TYPE
			SYNTAX BufferPercentag
			MAX-ACCESS read-only
			STATUS current
			DESCRIPTION
				"Maximum buffer level"
		::= { imb2000c01v1Entry 377 }

		-- 1.3.6.1.4.1.10106.3.101291.1.1.379
		imb2000c01v1MinBuffLev16 OBJECT-TYPE
			SYNTAX BufferPercentag
			MAX-ACCESS read-only
			STATUS current
			DESCRIPTION
				"Minimum buffer level"
		::= { imb2000c01v1Entry 379 }

		-- 1.3.6.1.4.1.10106.3.101291.1.1.381
		imb2000c01v1EnWc48k OBJECT-TYPE
			SYNTAX BitMask
			MAX-ACCESS read-write
			STATUS current
			DESCRIPTION
				"Allows enabling the generation of 48 kHz WordClock through the rear bus"
		::= { imb2000c01v1Entry 381 }

		-- 1.3.6.1.4.1.10106.3.101291.1.1.383
		imb2000c01v1EnBusRefTx OBJECT-TYPE
			SYNTAX Bit0No1Yes
			MAX-ACCESS read-write
			STATUS current
			DESCRIPTION
				"Sends reference to rear bus"
		::= { imb2000c01v1Entry 383 }

		-- 1.3.6.1.4.1.10106.3.101291.1.1.385
		imb2000c01v1Slot1S2mPres OBJECT-TYPE
			SYNTAX BitAct
			MAX-ACCESS read-only
			STATUS current
			DESCRIPTION
				"Slot1 S2M bus presence"
		::= { imb2000c01v1Entry 385 }

		-- 1.3.6.1.4.1.10106.3.101291.1.1.387
		imb2000c01v1Slot2S2mPres OBJECT-TYPE
			SYNTAX BitAct
			MAX-ACCESS read-only
			STATUS current
			DESCRIPTION
				"Slot2 S2M bus presence"
		::= { imb2000c01v1Entry 387 }

		-- 1.3.6.1.4.1.10106.3.101291.1.1.389
		imb2000c01v1Slot3S2mPres OBJECT-TYPE
			SYNTAX BitAct
			MAX-ACCESS read-only
			STATUS current
			DESCRIPTION
				"Slot3 S2M bus presence"
		::= { imb2000c01v1Entry 389 }

		-- 1.3.6.1.4.1.10106.3.101291.1.1.391
		imb2000c01v1Slot4S2mPres OBJECT-TYPE
			SYNTAX BitAct
			MAX-ACCESS read-only
			STATUS current
			DESCRIPTION
				"Slot4 S2M bus presence"
		::= { imb2000c01v1Entry 391 }

		-- 1.3.6.1.4.1.10106.3.101291.1.1.393
		imb2000c01v1Slot5S2mPres OBJECT-TYPE
			SYNTAX BitAct
			MAX-ACCESS read-only
			STATUS current
			DESCRIPTION
				"Slot5 S2M bus presence"
		::= { imb2000c01v1Entry 393 }

		-- 1.3.6.1.4.1.10106.3.101291.1.1.395
		imb2000c01v1Slot6S2mPres OBJECT-TYPE
			SYNTAX BitAct
			MAX-ACCESS read-only
			STATUS current
			DESCRIPTION
				"Slot6 S2M bus presence"
		::= { imb2000c01v1Entry 395 }

		-- 1.3.6.1.4.1.10106.3.101291.1.1.397
		imb2000c01v1Slot7S2mPres OBJECT-TYPE
			SYNTAX BitAct
			MAX-ACCESS read-only
			STATUS current
			DESCRIPTION
				"Slot7 S2M bus presence"
		::= { imb2000c01v1Entry 397 }

		-- 1.3.6.1.4.1.10106.3.101291.1.1.399
		imb2000c01v1Slot8S2mPres OBJECT-TYPE
			SYNTAX BitAct
			MAX-ACCESS read-only
			STATUS current
			DESCRIPTION
				"Slot8 S2M bus presence"
		::= { imb2000c01v1Entry 399 }

		-- 1.3.6.1.4.1.10106.3.101291.1.1.401
		imb2000c01v1BusRxFail OBJECT-TYPE
			SYNTAX BitFail
			MAX-ACCESS read-only
			STATUS current
			DESCRIPTION
				"Errores en el bus de audio"
		::= { imb2000c01v1Entry 401 }

		-- 1.3.6.1.4.1.10106.3.101291.1.1.403
		imb2000c01v1MadiTxNCh OBJECT-TYPE
			SYNTAX MadiNCh
			MAX-ACCESS read-write
			STATUS current
			DESCRIPTION
				"Tx MADI channels"
		::= { imb2000c01v1Entry 403 }

		-- 1.3.6.1.4.1.10106.3.101291.1.1.405
		imb2000c01v1ShufOk OBJECT-TYPE
			SYNTAX BitFailN
			MAX-ACCESS read-only
			STATUS current
			DESCRIPTION
				"Shuffling ok"
		::= { imb2000c01v1Entry 405 }

		-- 1.3.6.1.4.1.10106.3.101291.1.1.407
		imb2000c01v1LocalIp1Add3 OBJECT-TYPE
			SYNTAX Uint8
			MAX-ACCESS read-write
			STATUS current
			DESCRIPTION
				"IP address (3)"
		::= { imb2000c01v1Entry 407 }

		-- 1.3.6.1.4.1.10106.3.101291.1.1.409
		imb2000c01v1LocalIp1Add2 OBJECT-TYPE
			SYNTAX Uint8
			MAX-ACCESS read-write
			STATUS current
			DESCRIPTION
				"IP address (2)"
		::= { imb2000c01v1Entry 409 }

		-- 1.3.6.1.4.1.10106.3.101291.1.1.411
		imb2000c01v1LocalIp1Add1 OBJECT-TYPE
			SYNTAX Uint8
			MAX-ACCESS read-write
			STATUS current
			DESCRIPTION
				"IP address (1)"
		::= { imb2000c01v1Entry 411 }

		-- 1.3.6.1.4.1.10106.3.101291.1.1.413
		imb2000c01v1LocalIp1Add0 OBJECT-TYPE
			SYNTAX Uint8
			MAX-ACCESS read-write
			STATUS current
			DESCRIPTION
				"IP address (0)"
		::= { imb2000c01v1Entry 413 }

		-- 1.3.6.1.4.1.10106.3.101291.1.1.415
		imb2000c01v1LocalIp1Msk3 OBJECT-TYPE
			SYNTAX Uint8
			MAX-ACCESS read-write
			STATUS current
			DESCRIPTION
				"IP mask (3)"
		::= { imb2000c01v1Entry 415 }

		-- 1.3.6.1.4.1.10106.3.101291.1.1.417
		imb2000c01v1LocalIp1Msk2 OBJECT-TYPE
			SYNTAX Uint8
			MAX-ACCESS read-write
			STATUS current
			DESCRIPTION
				"IP mask (2)"
		::= { imb2000c01v1Entry 417 }

		-- 1.3.6.1.4.1.10106.3.101291.1.1.419
		imb2000c01v1LocalIp1Msk1 OBJECT-TYPE
			SYNTAX Uint8
			MAX-ACCESS read-write
			STATUS current
			DESCRIPTION
				"IP mask (1)"
		::= { imb2000c01v1Entry 419 }

		-- 1.3.6.1.4.1.10106.3.101291.1.1.421
		imb2000c01v1LocalIp1Msk0 OBJECT-TYPE
			SYNTAX Uint8
			MAX-ACCESS read-write
			STATUS current
			DESCRIPTION
				"IP mask (0)"
		::= { imb2000c01v1Entry 421 }

		-- 1.3.6.1.4.1.10106.3.101291.1.1.423
		imb2000c01v1Vlan1Enable OBJECT-TYPE
			SYNTAX Bit0No1Yes
			MAX-ACCESS read-write
			STATUS current
			DESCRIPTION
				"VLAN Enable"
		::= { imb2000c01v1Entry 423 }

		-- 1.3.6.1.4.1.10106.3.101291.1.1.425
		imb2000c01v1VlanPriority1 OBJECT-TYPE
			SYNTAX Uint3
			MAX-ACCESS read-write
			STATUS current
			DESCRIPTION
				"VLAN Priority"
		::= { imb2000c01v1Entry 425 }

		-- 1.3.6.1.4.1.10106.3.101291.1.1.427
		imb2000c01v1Vlan1Id OBJECT-TYPE
			SYNTAX Uint12
			MAX-ACCESS read-write
			STATUS current
			DESCRIPTION
				"VLAN ID"
		::= { imb2000c01v1Entry 427 }

		-- 1.3.6.1.4.1.10106.3.101291.1.1.429
		imb2000c01v1LocalIp2Add3 OBJECT-TYPE
			SYNTAX Uint8
			MAX-ACCESS read-write
			STATUS current
			DESCRIPTION
				"IP address (3)"
		::= { imb2000c01v1Entry 429 }

		-- 1.3.6.1.4.1.10106.3.101291.1.1.431
		imb2000c01v1LocalIp2Add2 OBJECT-TYPE
			SYNTAX Uint8
			MAX-ACCESS read-write
			STATUS current
			DESCRIPTION
				"IP address (2)"
		::= { imb2000c01v1Entry 431 }

		-- 1.3.6.1.4.1.10106.3.101291.1.1.433
		imb2000c01v1LocalIp2Add1 OBJECT-TYPE
			SYNTAX Uint8
			MAX-ACCESS read-write
			STATUS current
			DESCRIPTION
				"IP address (1)"
		::= { imb2000c01v1Entry 433 }

		-- 1.3.6.1.4.1.10106.3.101291.1.1.435
		imb2000c01v1LocalIp2Add0 OBJECT-TYPE
			SYNTAX Uint8
			MAX-ACCESS read-write
			STATUS current
			DESCRIPTION
				"IP address (0)"
		::= { imb2000c01v1Entry 435 }

		-- 1.3.6.1.4.1.10106.3.101291.1.1.437
		imb2000c01v1LocalIp2Msk3 OBJECT-TYPE
			SYNTAX Uint8
			MAX-ACCESS read-write
			STATUS current
			DESCRIPTION
				"IP mask (3)"
		::= { imb2000c01v1Entry 437 }

		-- 1.3.6.1.4.1.10106.3.101291.1.1.439
		imb2000c01v1LocalIp2Msk2 OBJECT-TYPE
			SYNTAX Uint8
			MAX-ACCESS read-write
			STATUS current
			DESCRIPTION
				"IP mask (2)"
		::= { imb2000c01v1Entry 439 }

		-- 1.3.6.1.4.1.10106.3.101291.1.1.441
		imb2000c01v1LocalIp2Msk1 OBJECT-TYPE
			SYNTAX Uint8
			MAX-ACCESS read-write
			STATUS current
			DESCRIPTION
				"IP mask (1)"
		::= { imb2000c01v1Entry 441 }

		-- 1.3.6.1.4.1.10106.3.101291.1.1.443
		imb2000c01v1LocalIp2Msk0 OBJECT-TYPE
			SYNTAX Uint8
			MAX-ACCESS read-write
			STATUS current
			DESCRIPTION
				"IP mask (0)"
		::= { imb2000c01v1Entry 443 }

		-- 1.3.6.1.4.1.10106.3.101291.1.1.445
		imb2000c01v1Vlan2Enable OBJECT-TYPE
			SYNTAX Bit0No1Yes
			MAX-ACCESS read-write
			STATUS current
			DESCRIPTION
				"VLAN Enable"
		::= { imb2000c01v1Entry 445 }

		-- 1.3.6.1.4.1.10106.3.101291.1.1.447
		imb2000c01v1VlanPriority2 OBJECT-TYPE
			SYNTAX Uint3
			MAX-ACCESS read-write
			STATUS current
			DESCRIPTION
				"VLAN Priority"
		::= { imb2000c01v1Entry 447 }

		-- 1.3.6.1.4.1.10106.3.101291.1.1.449
		imb2000c01v1Vlan2Id OBJECT-TYPE
			SYNTAX Uint12
			MAX-ACCESS read-write
			STATUS current
			DESCRIPTION
				"VLAN ID"
		::= { imb2000c01v1Entry 449 }

		-- 1.3.6.1.4.1.10106.3.101291.1.1.451
		imb2000c01v1LocalIp3Add3 OBJECT-TYPE
			SYNTAX Uint8
			MAX-ACCESS read-write
			STATUS current
			DESCRIPTION
				"IP address (3)"
		::= { imb2000c01v1Entry 451 }

		-- 1.3.6.1.4.1.10106.3.101291.1.1.453
		imb2000c01v1LocalIp3Add2 OBJECT-TYPE
			SYNTAX Uint8
			MAX-ACCESS read-write
			STATUS current
			DESCRIPTION
				"IP address (2)"
		::= { imb2000c01v1Entry 453 }

		-- 1.3.6.1.4.1.10106.3.101291.1.1.455
		imb2000c01v1LocalIp3Add1 OBJECT-TYPE
			SYNTAX Uint8
			MAX-ACCESS read-write
			STATUS current
			DESCRIPTION
				"IP address (1)"
		::= { imb2000c01v1Entry 455 }

		-- 1.3.6.1.4.1.10106.3.101291.1.1.457
		imb2000c01v1LocalIpAdd0 OBJECT-TYPE
			SYNTAX Uint8
			MAX-ACCESS read-write
			STATUS current
			DESCRIPTION
				"IP address (0)"
		::= { imb2000c01v1Entry 457 }

		-- 1.3.6.1.4.1.10106.3.101291.1.1.459
		imb2000c01v1LocalIp3Msk3 OBJECT-TYPE
			SYNTAX Uint8
			MAX-ACCESS read-write
			STATUS current
			DESCRIPTION
				"IP mask (3)"
		::= { imb2000c01v1Entry 459 }

		-- 1.3.6.1.4.1.10106.3.101291.1.1.461
		imb2000c01v1LocalIp3Msk2 OBJECT-TYPE
			SYNTAX Uint8
			MAX-ACCESS read-write
			STATUS current
			DESCRIPTION
				"IP mask (2)"
		::= { imb2000c01v1Entry 461 }

		-- 1.3.6.1.4.1.10106.3.101291.1.1.463
		imb2000c01v1LocalIp3Msk1 OBJECT-TYPE
			SYNTAX Uint8
			MAX-ACCESS read-write
			STATUS current
			DESCRIPTION
				"IP mask (1)"
		::= { imb2000c01v1Entry 463 }

		-- 1.3.6.1.4.1.10106.3.101291.1.1.465
		imb2000c01v1LocalIp3Msk0 OBJECT-TYPE
			SYNTAX Uint8
			MAX-ACCESS read-write
			STATUS current
			DESCRIPTION
				"IP mask (0)"
		::= { imb2000c01v1Entry 465 }

		-- 1.3.6.1.4.1.10106.3.101291.1.1.467
		imb2000c01v1Vlan3Enable OBJECT-TYPE
			SYNTAX Bit0No1Yes
			MAX-ACCESS read-write
			STATUS current
			DESCRIPTION
				"VLAN Enable"
		::= { imb2000c01v1Entry 467 }

		-- 1.3.6.1.4.1.10106.3.101291.1.1.469
		imb2000c01v1VlanPriority3 OBJECT-TYPE
			SYNTAX Uint3
			MAX-ACCESS read-write
			STATUS current
			DESCRIPTION
				"VLAN Priority"
		::= { imb2000c01v1Entry 469 }

		-- 1.3.6.1.4.1.10106.3.101291.1.1.471
		imb2000c01v1Vlan3Id OBJECT-TYPE
			SYNTAX Uint12
			MAX-ACCESS read-write
			STATUS current
			DESCRIPTION
				"VLAN ID"
		::= { imb2000c01v1Entry 471 }

		-- 1.3.6.1.4.1.10106.3.101291.1.1.473
		imb2000c01v1LocalIp4Add3 OBJECT-TYPE
			SYNTAX Uint8
			MAX-ACCESS read-write
			STATUS current
			DESCRIPTION
				"IP address (3)"
		::= { imb2000c01v1Entry 473 }

		-- 1.3.6.1.4.1.10106.3.101291.1.1.475
		imb2000c01v1LocalIp4Add2 OBJECT-TYPE
			SYNTAX Uint8
			MAX-ACCESS read-write
			STATUS current
			DESCRIPTION
				"IP address (2)"
		::= { imb2000c01v1Entry 475 }

		-- 1.3.6.1.4.1.10106.3.101291.1.1.477
		imb2000c01v1LocalIp4Add1 OBJECT-TYPE
			SYNTAX Uint8
			MAX-ACCESS read-write
			STATUS current
			DESCRIPTION
				"IP address (1)"
		::= { imb2000c01v1Entry 477 }

		-- 1.3.6.1.4.1.10106.3.101291.1.1.479
		imb2000c01v1LocalIp4Add0 OBJECT-TYPE
			SYNTAX Uint8
			MAX-ACCESS read-write
			STATUS current
			DESCRIPTION
				"IP address (0)"
		::= { imb2000c01v1Entry 479 }

		-- 1.3.6.1.4.1.10106.3.101291.1.1.481
		imb2000c01v1LocalIp4Msk3 OBJECT-TYPE
			SYNTAX Uint8
			MAX-ACCESS read-write
			STATUS current
			DESCRIPTION
				"IP mask (3)"
		::= { imb2000c01v1Entry 481 }

		-- 1.3.6.1.4.1.10106.3.101291.1.1.483
		imb2000c01v1LocalIp4Msk2 OBJECT-TYPE
			SYNTAX Uint8
			MAX-ACCESS read-write
			STATUS current
			DESCRIPTION
				"IP mask (2)"
		::= { imb2000c01v1Entry 483 }

		-- 1.3.6.1.4.1.10106.3.101291.1.1.485
		imb2000c01v1LocalIp4Msk1 OBJECT-TYPE
			SYNTAX Uint8
			MAX-ACCESS read-write
			STATUS current
			DESCRIPTION
				"IP mask (1)"
		::= { imb2000c01v1Entry 485 }

		-- 1.3.6.1.4.1.10106.3.101291.1.1.487
		imb2000c01v1LocalIp4Msk0 OBJECT-TYPE
			SYNTAX Uint8
			MAX-ACCESS read-write
			STATUS current
			DESCRIPTION
				"IP mask (0)"
		::= { imb2000c01v1Entry 487 }

		-- 1.3.6.1.4.1.10106.3.101291.1.1.489
		imb2000c01v1Vlan4Enable OBJECT-TYPE
			SYNTAX Bit0No1Yes
			MAX-ACCESS read-write
			STATUS current
			DESCRIPTION
				"VLAN Enable"
		::= { imb2000c01v1Entry 489 }

		-- 1.3.6.1.4.1.10106.3.101291.1.1.491
		imb2000c01v1VlanPriority4 OBJECT-TYPE
			SYNTAX Uint3
			MAX-ACCESS read-write
			STATUS current
			DESCRIPTION
				"VLAN Priority"
		::= { imb2000c01v1Entry 491 }

		-- 1.3.6.1.4.1.10106.3.101291.1.1.493
		imb2000c01v1Vlan4Id OBJECT-TYPE
			SYNTAX Uint12
			MAX-ACCESS read-write
			STATUS current
			DESCRIPTION
				"VLAN ID"
		::= { imb2000c01v1Entry 493 }

		-- 1.3.6.1.4.1.10106.3.101291.1.1.495
		imb2000c01v1SysError OBJECT-TYPE
			SYNTAX SysError0
			MAX-ACCESS read-only
			STATUS current
			DESCRIPTION
				"System error. (Irrecoverable alarm or event)"
		::= { imb2000c01v1Entry 495 }

		-- 1.3.6.1.4.1.10106.3.101291.1.1.497
		imb2000c01v1PtpIntSelected OBJECT-TYPE
			SYNTAX PtpStatus
			MAX-ACCESS read-only
			STATUS current
			DESCRIPTION
				"PTP interface selected"
		::= { imb2000c01v1Entry 497 }

		-- 1.3.6.1.4.1.10106.3.101291.1.1.499
		imb2000c01v1TxWorkinStat1 OBJECT-TYPE
			SYNTAX BitFailN
			MAX-ACCESS read-only
			STATUS current
			DESCRIPTION
				"TX 1 transmitting"
		::= { imb2000c01v1Entry 499 }

		-- 1.3.6.1.4.1.10106.3.101291.1.1.501
		imb2000c01v1ArpValid1 OBJECT-TYPE
			SYNTAX BitFailN
			MAX-ACCESS read-only
			STATUS current
			DESCRIPTION
				"TX 1 valid ARP response (Unicast mode)"
		::= { imb2000c01v1Entry 501 }

		-- 1.3.6.1.4.1.10106.3.101291.1.1.503
		imb2000c01v1IcmpError1 OBJECT-TYPE
			SYNTAX BitFailN
			MAX-ACCESS read-only
			STATUS current
			DESCRIPTION
				"TX 1 destination unreachable (ICMP destination unrechable packets received)"
		::= { imb2000c01v1Entry 503 }

		-- 1.3.6.1.4.1.10106.3.101291.1.1.505
		imb2000c01v1TxWorkinStat2 OBJECT-TYPE
			SYNTAX BitFailN
			MAX-ACCESS read-only
			STATUS current
			DESCRIPTION
				"TX 2 transmitting"
		::= { imb2000c01v1Entry 505 }

		-- 1.3.6.1.4.1.10106.3.101291.1.1.507
		imb2000c01v1ArpValid2 OBJECT-TYPE
			SYNTAX BitFailN
			MAX-ACCESS read-only
			STATUS current
			DESCRIPTION
				"TX 2 valid ARP response (Unicast mode)"
		::= { imb2000c01v1Entry 507 }

		-- 1.3.6.1.4.1.10106.3.101291.1.1.509
		imb2000c01v1IcmpError2 OBJECT-TYPE
			SYNTAX BitFailN
			MAX-ACCESS read-only
			STATUS current
			DESCRIPTION
				"TX 2 destination unreachable (ICMP destination unrechable packets received)"
		::= { imb2000c01v1Entry 509 }

		-- 1.3.6.1.4.1.10106.3.101291.1.1.511
		imb2000c01v1TxWorkinStat3 OBJECT-TYPE
			SYNTAX BitFailN
			MAX-ACCESS read-only
			STATUS current
			DESCRIPTION
				"TX 3 transmitting"
		::= { imb2000c01v1Entry 511 }

		-- 1.3.6.1.4.1.10106.3.101291.1.1.513
		imb2000c01v1ArpValid3 OBJECT-TYPE
			SYNTAX BitFailN
			MAX-ACCESS read-only
			STATUS current
			DESCRIPTION
				"TX 3 valid ARP response (Unicast mode)"
		::= { imb2000c01v1Entry 513 }

		-- 1.3.6.1.4.1.10106.3.101291.1.1.515
		imb2000c01v1IcmpError3 OBJECT-TYPE
			SYNTAX BitFailN
			MAX-ACCESS read-only
			STATUS current
			DESCRIPTION
				"TX 3 destination unreachable (ICMP destination unrechable packets received)"
		::= { imb2000c01v1Entry 515 }

		-- 1.3.6.1.4.1.10106.3.101291.1.1.517
		imb2000c01v1TxWorkinStat4 OBJECT-TYPE
			SYNTAX BitFailN
			MAX-ACCESS read-only
			STATUS current
			DESCRIPTION
				"TX 4 transmitting"
		::= { imb2000c01v1Entry 517 }

		-- 1.3.6.1.4.1.10106.3.101291.1.1.519
		imb2000c01v1ArpValid4 OBJECT-TYPE
			SYNTAX BitFailN
			MAX-ACCESS read-only
			STATUS current
			DESCRIPTION
				"TX 4 valid ARP response (Unicast mode)"
		::= { imb2000c01v1Entry 519 }

		-- 1.3.6.1.4.1.10106.3.101291.1.1.521
		imb2000c01v1IcmpError4 OBJECT-TYPE
			SYNTAX BitFailN
			MAX-ACCESS read-only
			STATUS current
			DESCRIPTION
				"TX 4 destination unreachable (ICMP destination unrechable packets received)"
		::= { imb2000c01v1Entry 521 }

		-- 1.3.6.1.4.1.10106.3.101291.1.1.523
		imb2000c01v1TxWorkinStat5 OBJECT-TYPE
			SYNTAX BitFailN
			MAX-ACCESS read-only
			STATUS current
			DESCRIPTION
				"TX 5 transmitting"
		::= { imb2000c01v1Entry 523 }

		-- 1.3.6.1.4.1.10106.3.101291.1.1.525
		imb2000c01v1ArpValid5 OBJECT-TYPE
			SYNTAX BitFailN
			MAX-ACCESS read-only
			STATUS current
			DESCRIPTION
				"TX 5 valid ARP response (Unicast mode)"
		::= { imb2000c01v1Entry 525 }

		-- 1.3.6.1.4.1.10106.3.101291.1.1.527
		imb2000c01v1IcmpError5 OBJECT-TYPE
			SYNTAX BitFailN
			MAX-ACCESS read-only
			STATUS current
			DESCRIPTION
				"TX 5 destination unreachable (ICMP destination unrechable packets received)"
		::= { imb2000c01v1Entry 527 }

		-- 1.3.6.1.4.1.10106.3.101291.1.1.529
		imb2000c01v1TxWorkinStat6 OBJECT-TYPE
			SYNTAX BitFailN
			MAX-ACCESS read-only
			STATUS current
			DESCRIPTION
				"TX 6 transmitting"
		::= { imb2000c01v1Entry 529 }

		-- 1.3.6.1.4.1.10106.3.101291.1.1.531
		imb2000c01v1ArpValid6 OBJECT-TYPE
			SYNTAX BitFailN
			MAX-ACCESS read-only
			STATUS current
			DESCRIPTION
				"TX 6 valid ARP response (Unicast mode)"
		::= { imb2000c01v1Entry 531 }

		-- 1.3.6.1.4.1.10106.3.101291.1.1.533
		imb2000c01v1IcmpError6 OBJECT-TYPE
			SYNTAX BitFailN
			MAX-ACCESS read-only
			STATUS current
			DESCRIPTION
				"TX 6 destination unreachable (ICMP destination unrechable packets received)"
		::= { imb2000c01v1Entry 533 }

		-- 1.3.6.1.4.1.10106.3.101291.1.1.535
		imb2000c01v1TxWorkinStat7 OBJECT-TYPE
			SYNTAX BitFailN
			MAX-ACCESS read-only
			STATUS current
			DESCRIPTION
				"TX 7 transmitting"
		::= { imb2000c01v1Entry 535 }

		-- 1.3.6.1.4.1.10106.3.101291.1.1.537
		imb2000c01v1ArpValid7 OBJECT-TYPE
			SYNTAX BitFailN
			MAX-ACCESS read-only
			STATUS current
			DESCRIPTION
				"TX 7 valid ARP response (Unicast mode)"
		::= { imb2000c01v1Entry 537 }

		-- 1.3.6.1.4.1.10106.3.101291.1.1.539
		imb2000c01v1IcmpError7 OBJECT-TYPE
			SYNTAX BitFailN
			MAX-ACCESS read-only
			STATUS current
			DESCRIPTION
				"TX 7 destination unreachable (ICMP destination unrechable packets received)"
		::= { imb2000c01v1Entry 539 }

		-- 1.3.6.1.4.1.10106.3.101291.1.1.541
		imb2000c01v1TxWorkinStat8 OBJECT-TYPE
			SYNTAX BitFailN
			MAX-ACCESS read-only
			STATUS current
			DESCRIPTION
				"TX 8 transmitting"
		::= { imb2000c01v1Entry 541 }

		-- 1.3.6.1.4.1.10106.3.101291.1.1.543
		imb2000c01v1ArpValid8 OBJECT-TYPE
			SYNTAX BitFailN
			MAX-ACCESS read-only
			STATUS current
			DESCRIPTION
				"TX 8 valid ARP response (Unicast mode)"
		::= { imb2000c01v1Entry 543 }

		-- 1.3.6.1.4.1.10106.3.101291.1.1.545
		imb2000c01v1IcmpError8 OBJECT-TYPE
			SYNTAX BitFailN
			MAX-ACCESS read-only
			STATUS current
			DESCRIPTION
				"TX 8 destination unreachable (ICMP destination unrechable packets received)"
		::= { imb2000c01v1Entry 545 }

		-- 1.3.6.1.4.1.10106.3.101291.1.1.547
		imb2000c01v1PtpState OBJECT-TYPE
			SYNTAX PtpState
			MAX-ACCESS read-only
			STATUS current
			DESCRIPTION
				"Indicates the PTP state"
		::= { imb2000c01v1Entry 547 }

		-- 1.3.6.1.4.1.10106.3.101291.1.1.549
		imb2000c01v1MadiRxOk OBJECT-TYPE
			SYNTAX BitFailN
			MAX-ACCESS read-only
			STATUS current
			DESCRIPTION
				"MADI reception ok"
		::= { imb2000c01v1Entry 549 }

		-- 1.3.6.1.4.1.10106.3.101291.1.1.551
		imb2000c01v1MadiRxNCh OBJECT-TYPE
			SYNTAX Uint7
			MAX-ACCESS read-only
			STATUS current
			DESCRIPTION
				"Amount of MADI RX channels"
		::= { imb2000c01v1Entry 551 }

		-- 1.3.6.1.4.1.10106.3.101291.1.1.553
		imb2000c01v1ClkStatus OBJECT-TYPE
			SYNTAX ClkStatus
			MAX-ACCESS read-only
			STATUS current
			DESCRIPTION
				"Clock status"
		::= { imb2000c01v1Entry 553 }

		-- 1.3.6.1.4.1.10106.3.101291.1.1.555
		imb2000c01v1ClockOffset OBJECT-TYPE
			SYNTAX TimeX1Us
			MAX-ACCESS read-only
			STATUS current
			DESCRIPTION
				"Timestamp offset"
		::= { imb2000c01v1Entry 555 }

		-- 1.3.6.1.4.1.10106.3.101291.1.1.557
		imb2000c01v1ClockDelay OBJECT-TYPE
			SYNTAX TimeX1Us
			MAX-ACCESS read-only
			STATUS current
			DESCRIPTION
				"Link delay"
		::= { imb2000c01v1Entry 557 }

		-- 1.3.6.1.4.1.10106.3.101291.1.1.559
		imb2000c01v1RxTimeRst OBJECT-TYPE
			SYNTAX TimeS6
			MAX-ACCESS read-only
			STATUS current
			DESCRIPTION
				"Elapsed time since last reset"
		::= { imb2000c01v1Entry 559 }

		-- 1.3.6.1.4.1.10106.3.101291.1.1.561
		imb2000c01v1Link1 OBJECT-TYPE
			SYNTAX Ipa2EtherStat
			MAX-ACCESS read-only
			STATUS current
			DESCRIPTION
				"Ethernet conection status"
		::= { imb2000c01v1Entry 561 }

		-- 1.3.6.1.4.1.10106.3.101291.1.1.563
		imb2000c01v1System1 OBJECT-TYPE
			SYNTAX Ipa2EtherSys
			MAX-ACCESS read-only
			STATUS current
			DESCRIPTION
				"Ethernet conection system"
		::= { imb2000c01v1Entry 563 }

		-- 1.3.6.1.4.1.10106.3.101291.1.1.565
		imb2000c01v1Link2 OBJECT-TYPE
			SYNTAX Ipa2EtherStat
			MAX-ACCESS read-only
			STATUS current
			DESCRIPTION
				"Ethernet conection status"
		::= { imb2000c01v1Entry 565 }

		-- 1.3.6.1.4.1.10106.3.101291.1.1.567
		imb2000c01v1System2 OBJECT-TYPE
			SYNTAX Ipa2EtherSys
			MAX-ACCESS read-only
			STATUS current
			DESCRIPTION
				"Ethernet conection system"
		::= { imb2000c01v1Entry 567 }

		-- 1.3.6.1.4.1.10106.3.101291.1.1.569
		imb2000c01v1SerialNo OBJECT-TYPE
			SYNTAX SerialNo
			MAX-ACCESS read-only
			STATUS current
			DESCRIPTION
				"Serial number"
		::= { imb2000c01v1Entry 569 }

		-- 1.3.6.1.4.1.10106.3.523601
		swc2000c01v1 OBJECT IDENTIFIER ::= { albalaProducts 523601 }

		-- 1.3.6.1.4.1.10106.3.523601.1
		swc2000c01v1Table  OBJECT-TYPE
			SYNTAX SEQUENCE OF Swc2000c01v1Entry
			MAX-ACCESS not-accessible
			STATUS current
			DESCRIPTION
				"Module  SWC2000C01V1 Table"
			::= { swc2000c01v1 1 }

		-- 1.3.6.1.4.1.10106.3.523601.1.1
		swc2000c01v1Entry  OBJECT-TYPE
			SYNTAX Swc2000c01v1Entry
			MAX-ACCESS not-accessible
			STATUS current
			DESCRIPTION
				"Module SWC2000C01V1 Entry"
			INDEX { swc2000c01v1Index }
			::= { swc2000c01v1Table 1 }

			Swc2000c01v1Entry ::=
			SEQUENCE {
				swc2000c01v1Index
				ModuleIndex,
				swc2000c01v1Gpo1
				Bit0Ina1Act,
				swc2000c01v1Gpo2
				Bit0Ina1Act,
				swc2000c01v1Gpo3
				Bit0Ina1Act,
				swc2000c01v1Gpo4
				Bit0Ina1Act,
				swc2000c01v1InvertGpi1Pol
				Bit0No1Yes,
				swc2000c01v1InvertGpi2Pol
				Bit0No1Yes,
				swc2000c01v1InvertGpi3Pol
				Bit0No1Yes,
				swc2000c01v1InvertGpi4Pol
				Bit0No1Yes,
				swc2000c01v1InvertGpo1Pol
				Bit0No1Yes,
				swc2000c01v1InvertGpo2Pol
				Bit0No1Yes,
				swc2000c01v1InvertGpo3Pol
				Bit0No1Yes,
				swc2000c01v1InvertGpo4Pol
				Bit0No1Yes,
				swc2000c01v1Gpi1
				Bit0Ina1Act,
				swc2000c01v1Gpi1TrapEnable
				AlarmEnable,
				swc2000c01v1Gpi2
				Bit0Ina1Act,
				swc2000c01v1Gpi2TrapEnable
				AlarmEnable,
				swc2000c01v1Gpi3
				Bit0Ina1Act,
				swc2000c01v1Gpi3TrapEnable
				AlarmEnable,
				swc2000c01v1Gpi4
				Bit0Ina1Act,
				swc2000c01v1Gpi4TrapEnable
				AlarmEnable,
				swc2000c01v1RedBoard
				Bit0No1Yes,
				swc2000c01v1RedBoardTrapEnable
				AlarmEnable,
				swc2000c01v1EthLink
				Bit0No1Yes,
				swc2000c01v1EthLinkTrapEnable
				AlarmEnable,
				swc2000c01v1EthRedAct
				Bit0No1Yes,
				swc2000c01v1EthRedActTrapEnable
				AlarmEnable,
				swc2000c01v1SerialNo
				SerialNo
			 }

		-- 1.3.6.1.4.1.10106.3.101291.1.1.1
		swc2000c01v1Index OBJECT-TYPE
			SYNTAX ModuleIndex
			MAX-ACCESS read-only
			STATUS current
			DESCRIPTION
				"Index of SWC2000C01V1 Table"
		::= { swc2000c01v1Entry 1 }

		-- 1.3.6.1.4.1.10106.3.101291.1.1.3
		swc2000c01v1Gpo1 OBJECT-TYPE
			SYNTAX Bit0Ina1Act
			MAX-ACCESS read-write
			STATUS current
			DESCRIPTION
				"Allows control of GPO1"
		::= { swc2000c01v1Entry 3 }

		-- 1.3.6.1.4.1.10106.3.101291.1.1.5
		swc2000c01v1Gpo2 OBJECT-TYPE
			SYNTAX Bit0Ina1Act
			MAX-ACCESS read-write
			STATUS current
			DESCRIPTION
				"Allows control of GPO2"
		::= { swc2000c01v1Entry 5 }

		-- 1.3.6.1.4.1.10106.3.101291.1.1.7
		swc2000c01v1Gpo3 OBJECT-TYPE
			SYNTAX Bit0Ina1Act
			MAX-ACCESS read-write
			STATUS current
			DESCRIPTION
				"Allows control of GPO3"
		::= { swc2000c01v1Entry 7 }

		-- 1.3.6.1.4.1.10106.3.101291.1.1.9
		swc2000c01v1Gpo4 OBJECT-TYPE
			SYNTAX Bit0Ina1Act
			MAX-ACCESS read-write
			STATUS current
			DESCRIPTION
				"Allows control of GPO4"
		::= { swc2000c01v1Entry 9 }

		-- 1.3.6.1.4.1.10106.3.101291.1.1.11
		swc2000c01v1InvertGpi1Pol OBJECT-TYPE
			SYNTAX Bit0No1Yes
			MAX-ACCESS read-write
			STATUS current
			DESCRIPTION
				"Changes GPI1 polarity to normally closed"
		::= { swc2000c01v1Entry 11 }

		-- 1.3.6.1.4.1.10106.3.101291.1.1.13
		swc2000c01v1InvertGpi2Pol OBJECT-TYPE
			SYNTAX Bit0No1Yes
			MAX-ACCESS read-write
			STATUS current
			DESCRIPTION
				"Changes GPI2 polarity to normally closed"
		::= { swc2000c01v1Entry 13 }

		-- 1.3.6.1.4.1.10106.3.101291.1.1.15
		swc2000c01v1InvertGpi3Pol OBJECT-TYPE
			SYNTAX Bit0No1Yes
			MAX-ACCESS read-write
			STATUS current
			DESCRIPTION
				"Changes GPI3 polarity to normally closed"
		::= { swc2000c01v1Entry 15 }

		-- 1.3.6.1.4.1.10106.3.101291.1.1.17
		swc2000c01v1InvertGpi4Pol OBJECT-TYPE
			SYNTAX Bit0No1Yes
			MAX-ACCESS read-write
			STATUS current
			DESCRIPTION
				"Changes GPI4 polarity to normally closed"
		::= { swc2000c01v1Entry 17 }

		-- 1.3.6.1.4.1.10106.3.101291.1.1.19
		swc2000c01v1InvertGpo1Pol OBJECT-TYPE
			SYNTAX Bit0No1Yes
			MAX-ACCESS read-write
			STATUS current
			DESCRIPTION
				"Allows inverting GPO1 polarity"
		::= { swc2000c01v1Entry 19 }

		-- 1.3.6.1.4.1.10106.3.101291.1.1.21
		swc2000c01v1InvertGpo2Pol OBJECT-TYPE
			SYNTAX Bit0No1Yes
			MAX-ACCESS read-write
			STATUS current
			DESCRIPTION
				"Allows inverting GPO2 polarity"
		::= { swc2000c01v1Entry 21 }

		-- 1.3.6.1.4.1.10106.3.101291.1.1.23
		swc2000c01v1InvertGpo3Pol OBJECT-TYPE
			SYNTAX Bit0No1Yes
			MAX-ACCESS read-write
			STATUS current
			DESCRIPTION
				"Allows inverting GPO3 polarity"
		::= { swc2000c01v1Entry 23 }

		-- 1.3.6.1.4.1.10106.3.101291.1.1.25
		swc2000c01v1InvertGpo4Pol OBJECT-TYPE
			SYNTAX Bit0No1Yes
			MAX-ACCESS read-write
			STATUS current
			DESCRIPTION
				"Allows inverting GPO4 polarity"
		::= { swc2000c01v1Entry 25 }

		-- 1.3.6.1.4.1.10106.3.101291.1.1.27
		swc2000c01v1Gpi1 OBJECT-TYPE
			SYNTAX Bit0Ina1Act
			MAX-ACCESS read-only
			STATUS current
			DESCRIPTION
				"GPI1 status"
		::= { swc2000c01v1Entry 27 }

		-- 1.3.6.1.4.1.10106.3.101291.1.1.28
		swc2000c01v1Gpi1TrapEnable OBJECT-TYPE
			SYNTAX AlarmEnable
			MAX-ACCESS read-write
			STATUS current
			DESCRIPTION
				"GPI1 status Trap Enable"
		::= { swc2000c01v1Entry 28 }

		-- 1.3.6.1.4.1.10106.3.101291.1.1.29
		swc2000c01v1Gpi2 OBJECT-TYPE
			SYNTAX Bit0Ina1Act
			MAX-ACCESS read-only
			STATUS current
			DESCRIPTION
				"GPI2 status"
		::= { swc2000c01v1Entry 29 }

		-- 1.3.6.1.4.1.10106.3.101291.1.1.30
		swc2000c01v1Gpi2TrapEnable OBJECT-TYPE
			SYNTAX AlarmEnable
			MAX-ACCESS read-write
			STATUS current
			DESCRIPTION
				"GPI2 status Trap Enable"
		::= { swc2000c01v1Entry 30 }

		-- 1.3.6.1.4.1.10106.3.101291.1.1.31
		swc2000c01v1Gpi3 OBJECT-TYPE
			SYNTAX Bit0Ina1Act
			MAX-ACCESS read-only
			STATUS current
			DESCRIPTION
				"GPI3 status"
		::= { swc2000c01v1Entry 31 }

		-- 1.3.6.1.4.1.10106.3.101291.1.1.32
		swc2000c01v1Gpi3TrapEnable OBJECT-TYPE
			SYNTAX AlarmEnable
			MAX-ACCESS read-write
			STATUS current
			DESCRIPTION
				"GPI3 status Trap Enable"
		::= { swc2000c01v1Entry 32 }

		-- 1.3.6.1.4.1.10106.3.101291.1.1.33
		swc2000c01v1Gpi4 OBJECT-TYPE
			SYNTAX Bit0Ina1Act
			MAX-ACCESS read-only
			STATUS current
			DESCRIPTION
				"GPI4 status"
		::= { swc2000c01v1Entry 33 }

		-- 1.3.6.1.4.1.10106.3.101291.1.1.34
		swc2000c01v1Gpi4TrapEnable OBJECT-TYPE
			SYNTAX AlarmEnable
			MAX-ACCESS read-write
			STATUS current
			DESCRIPTION
				"GPI4 status Trap Enable"
		::= { swc2000c01v1Entry 34 }

		-- 1.3.6.1.4.1.10106.3.101291.1.1.35
		swc2000c01v1RedBoard OBJECT-TYPE
			SYNTAX Bit0No1Yes
			MAX-ACCESS read-only
			STATUS current
			DESCRIPTION
				"Indicates that there are two modules in redundant configuration"
		::= { swc2000c01v1Entry 35 }

		-- 1.3.6.1.4.1.10106.3.101291.1.1.36
		swc2000c01v1RedBoardTrapEnable OBJECT-TYPE
			SYNTAX AlarmEnable
			MAX-ACCESS read-write
			STATUS current
			DESCRIPTION
				"Indicates that there are two modules in redundant configuration Trap Enable"
		::= { swc2000c01v1Entry 36 }

		-- 1.3.6.1.4.1.10106.3.101291.1.1.37
		swc2000c01v1EthLink OBJECT-TYPE
			SYNTAX Bit0No1Yes
			MAX-ACCESS read-only
			STATUS current
			DESCRIPTION
				"Indicates that the Ethernet link is OK"
		::= { swc2000c01v1Entry 37 }

		-- 1.3.6.1.4.1.10106.3.101291.1.1.38
		swc2000c01v1EthLinkTrapEnable OBJECT-TYPE
			SYNTAX AlarmEnable
			MAX-ACCESS read-write
			STATUS current
			DESCRIPTION
				"Indicates that the Ethernet link is OK Trap Enable"
		::= { swc2000c01v1Entry 38 }

		-- 1.3.6.1.4.1.10106.3.101291.1.1.39
		swc2000c01v1EthRedAct OBJECT-TYPE
			SYNTAX Bit0No1Yes
			MAX-ACCESS read-only
			STATUS current
			DESCRIPTION
				"Indicates that this is the active module of the redundant configuration"
		::= { swc2000c01v1Entry 39 }

		-- 1.3.6.1.4.1.10106.3.101291.1.1.40
		swc2000c01v1EthRedActTrapEnable OBJECT-TYPE
			SYNTAX AlarmEnable
			MAX-ACCESS read-write
			STATUS current
			DESCRIPTION
				"Indicates that this is the active module of the redundant configuration Trap Enable"
		::= { swc2000c01v1Entry 40 }

		-- 1.3.6.1.4.1.10106.3.101291.1.1.41
		swc2000c01v1SerialNo OBJECT-TYPE
			SYNTAX SerialNo
			MAX-ACCESS read-only
			STATUS current
			DESCRIPTION
				"Serial number"
		::= { swc2000c01v1Entry 41 }

		-- 1.3.6.1.4.1.10106.3.524101
		psu2001c01v1 OBJECT IDENTIFIER ::= { albalaProducts 524101 }

		-- 1.3.6.1.4.1.10106.3.524101.1
		psu2001c01v1Table  OBJECT-TYPE
			SYNTAX SEQUENCE OF Psu2001c01v1Entry
			MAX-ACCESS not-accessible
			STATUS current
			DESCRIPTION
				"Module  PSU2001C01V1 Table"
			::= { psu2001c01v1 1 }

		-- 1.3.6.1.4.1.10106.3.524101.1.1
		psu2001c01v1Entry  OBJECT-TYPE
			SYNTAX Psu2001c01v1Entry
			MAX-ACCESS not-accessible
			STATUS current
			DESCRIPTION
				"Module PSU2001C01V1 Entry"
			INDEX { psu2001c01v1Index }
			::= { psu2001c01v1Table 1 }

			Psu2001c01v1Entry ::=
			SEQUENCE {
				psu2001c01v1Index
				ModuleIndex,
				psu2001c01v1PowerOff
				BitFail,
				psu2001c01v1PowerOffTrapEnable
				AlarmEnable,
				psu2001c01v1TempWarning
				BitFail,
				psu2001c01v1TempWarningTrapEnable
				AlarmEnable,
				psu2001c01v1TempFail
				BitFail,
				psu2001c01v1TempFailTrapEnable
				AlarmEnable,
				psu2001c01v1PwrWarning
				BitFail,
				psu2001c01v1PwrWarningTrapEnable
				AlarmEnable,
				psu2001c01v1PwrFail
				BitFail,
				psu2001c01v1PwrFailTrapEnable
				AlarmEnable,
				psu2001c01v1InputVolt
				PsuDcInpV,
				psu2001c01v1OutputPower
				PowerX1W,
				psu2001c01v1ActTemp
				Temperature0c1,
				psu2001c01v1MeanTemp
				Temperature0c1,
				psu2001c01v1MaxTemp
				Temperature0c1,
				psu2001c01v1PonHours
				TimeX1Hour,
				psu2001c01v1TotMaxTemp
				Temperature0c1,
				psu2001c01v1TotPonHours
				TimeX1Hour,
				psu2001c01v1TotPonTimes
				Uint16,
				psu2001c01v1SerialNo
				SerialNo
			 }

		-- 1.3.6.1.4.1.10106.3.101291.1.1.1
		psu2001c01v1Index OBJECT-TYPE
			SYNTAX ModuleIndex
			MAX-ACCESS read-only
			STATUS current
			DESCRIPTION
				"Index of PSU2001C01V1 Table"
		::= { psu2001c01v1Entry 1 }

		-- 1.3.6.1.4.1.10106.3.101291.1.1.3
		psu2001c01v1PowerOff OBJECT-TYPE
			SYNTAX BitFail
			MAX-ACCESS read-only
			STATUS current
			DESCRIPTION
				"Indicates the power supply status"
		::= { psu2001c01v1Entry 3 }

		-- 1.3.6.1.4.1.10106.3.101291.1.1.4
		psu2001c01v1PowerOffTrapEnable OBJECT-TYPE
			SYNTAX AlarmEnable
			MAX-ACCESS read-write
			STATUS current
			DESCRIPTION
				"Indicates the power supply status Trap Enable"
		::= { psu2001c01v1Entry 4 }

		-- 1.3.6.1.4.1.10106.3.101291.1.1.5
		psu2001c01v1TempWarning OBJECT-TYPE
			SYNTAX BitFail
			MAX-ACCESS read-only
			STATUS current
			DESCRIPTION
				"Indicates that actual temperature is over expected range"
		::= { psu2001c01v1Entry 5 }

		-- 1.3.6.1.4.1.10106.3.101291.1.1.6
		psu2001c01v1TempWarningTrapEnable OBJECT-TYPE
			SYNTAX AlarmEnable
			MAX-ACCESS read-write
			STATUS current
			DESCRIPTION
				"Indicates that actual temperature is over expected range Trap Enable"
		::= { psu2001c01v1Entry 6 }

		-- 1.3.6.1.4.1.10106.3.101291.1.1.7
		psu2001c01v1TempFail OBJECT-TYPE
			SYNTAX BitFail
			MAX-ACCESS read-only
			STATUS current
			DESCRIPTION
				"Indicates that actual temperature is over recommended range"
		::= { psu2001c01v1Entry 7 }

		-- 1.3.6.1.4.1.10106.3.101291.1.1.8
		psu2001c01v1TempFailTrapEnable OBJECT-TYPE
			SYNTAX AlarmEnable
			MAX-ACCESS read-write
			STATUS current
			DESCRIPTION
				"Indicates that actual temperature is over recommended range Trap Enable"
		::= { psu2001c01v1Entry 8 }

		-- 1.3.6.1.4.1.10106.3.101291.1.1.9
		psu2001c01v1PwrWarning OBJECT-TYPE
			SYNTAX BitFail
			MAX-ACCESS read-only
			STATUS current
			DESCRIPTION
				"Indicates that actual output power is over expected range"
		::= { psu2001c01v1Entry 9 }

		-- 1.3.6.1.4.1.10106.3.101291.1.1.10
		psu2001c01v1PwrWarningTrapEnable OBJECT-TYPE
			SYNTAX AlarmEnable
			MAX-ACCESS read-write
			STATUS current
			DESCRIPTION
				"Indicates that actual output power is over expected range Trap Enable"
		::= { psu2001c01v1Entry 10 }

		-- 1.3.6.1.4.1.10106.3.101291.1.1.11
		psu2001c01v1PwrFail OBJECT-TYPE
			SYNTAX BitFail
			MAX-ACCESS read-only
			STATUS current
			DESCRIPTION
				"Indicates that actual output power is over allowed range"
		::= { psu2001c01v1Entry 11 }

		-- 1.3.6.1.4.1.10106.3.101291.1.1.12
		psu2001c01v1PwrFailTrapEnable OBJECT-TYPE
			SYNTAX AlarmEnable
			MAX-ACCESS read-write
			STATUS current
			DESCRIPTION
				"Indicates that actual output power is over allowed range Trap Enable"
		::= { psu2001c01v1Entry 12 }

		-- 1.3.6.1.4.1.10106.3.101291.1.1.13
		psu2001c01v1InputVolt OBJECT-TYPE
			SYNTAX PsuDcInpV
			MAX-ACCESS read-only
			STATUS current
			DESCRIPTION
				"Displays the DC input voltaje"
		::= { psu2001c01v1Entry 13 }

		-- 1.3.6.1.4.1.10106.3.101291.1.1.15
		psu2001c01v1OutputPower OBJECT-TYPE
			SYNTAX PowerX1W
			MAX-ACCESS read-only
			STATUS current
			DESCRIPTION
				"Displays the delivered output power"
		::= { psu2001c01v1Entry 15 }

		-- 1.3.6.1.4.1.10106.3.101291.1.1.17
		psu2001c01v1ActTemp OBJECT-TYPE
			SYNTAX Temperature0c1
			MAX-ACCESS read-only
			STATUS current
			DESCRIPTION
				"Displays internal actual temperature"
		::= { psu2001c01v1Entry 17 }

		-- 1.3.6.1.4.1.10106.3.101291.1.1.19
		psu2001c01v1MeanTemp OBJECT-TYPE
			SYNTAX Temperature0c1
			MAX-ACCESS read-only
			STATUS current
			DESCRIPTION
				"Displays internal mean temperature"
		::= { psu2001c01v1Entry 19 }

		-- 1.3.6.1.4.1.10106.3.101291.1.1.21
		psu2001c01v1MaxTemp OBJECT-TYPE
			SYNTAX Temperature0c1
			MAX-ACCESS read-only
			STATUS current
			DESCRIPTION
				"Displays internal maximun temperature"
		::= { psu2001c01v1Entry 21 }

		-- 1.3.6.1.4.1.10106.3.101291.1.1.23
		psu2001c01v1PonHours OBJECT-TYPE
			SYNTAX TimeX1Hour
			MAX-ACCESS read-only
			STATUS current
			DESCRIPTION
				"Displays module power on time"
		::= { psu2001c01v1Entry 23 }

		-- 1.3.6.1.4.1.10106.3.101291.1.1.25
		psu2001c01v1TotMaxTemp OBJECT-TYPE
			SYNTAX Temperature0c1
			MAX-ACCESS read-only
			STATUS current
			DESCRIPTION
				"Displays internal maximun tempertature since first power on"
		::= { psu2001c01v1Entry 25 }

		-- 1.3.6.1.4.1.10106.3.101291.1.1.27
		psu2001c01v1TotPonHours OBJECT-TYPE
			SYNTAX TimeX1Hour
			MAX-ACCESS read-only
			STATUS current
			DESCRIPTION
				"Displays module power on time since first power on"
		::= { psu2001c01v1Entry 27 }

		-- 1.3.6.1.4.1.10106.3.101291.1.1.29
		psu2001c01v1TotPonTimes OBJECT-TYPE
			SYNTAX Uint16
			MAX-ACCESS read-only
			STATUS current
			DESCRIPTION
				"Displays module power on events since first power on"
		::= { psu2001c01v1Entry 29 }

		-- 1.3.6.1.4.1.10106.3.101291.1.1.31
		psu2001c01v1SerialNo OBJECT-TYPE
			SYNTAX SerialNo
			MAX-ACCESS read-only
			STATUS current
			DESCRIPTION
				"Serial number"
		::= { psu2001c01v1Entry 31 }

		-- 1.3.6.1.4.1.10106.3.527201
		eol2000c01v1 OBJECT IDENTIFIER ::= { albalaProducts 527201 }

		-- 1.3.6.1.4.1.10106.3.527201.1
		eol2000c01v1Table  OBJECT-TYPE
			SYNTAX SEQUENCE OF Eol2000c01v1Entry
			MAX-ACCESS not-accessible
			STATUS current
			DESCRIPTION
				"Module  EOL2000C01V1 Table"
			::= { eol2000c01v1 1 }

		-- 1.3.6.1.4.1.10106.3.527201.1.1
		eol2000c01v1Entry  OBJECT-TYPE
			SYNTAX Eol2000c01v1Entry
			MAX-ACCESS not-accessible
			STATUS current
			DESCRIPTION
				"Module EOL2000C01V1 Entry"
			INDEX { eol2000c01v1Index }
			::= { eol2000c01v1Table 1 }

			Eol2000c01v1Entry ::=
			SEQUENCE {
				eol2000c01v1Index
				ModuleIndex,
				eol2000c01v1GenlockMode
				Bit0Ele1Opt,
				eol2000c01v1Format
				SdiHd3gFmt6,
				eol2000c01v1Bits
				Bit024120,
				eol2000c01v1DeleteGr1
				Bit0No1Yes,
				eol2000c01v1DeleteGr2
				Bit0No1Yes,
				eol2000c01v1DeleteGr3
				Bit0No1Yes,
				eol2000c01v1DeleteGr4
				Bit0No1Yes,
				eol2000c01v1FreezeTout
				TimeS2,
				eol2000c01v1InFormat1
				SdiHd3gFmt3,
				eol2000c01v1InFormat1TrapEnable
				AlarmEnable,
				eol2000c01v1InFormat2
				SdiHd3gFmt3,
				eol2000c01v1RefUnlock
				BitFail,
				eol2000c01v1RefUnlockTrapEnable
				AlarmEnable,
				eol2000c01v1NoSigA
				BitFail,
				eol2000c01v1NoSigATrapEnable
				AlarmEnable,
				eol2000c01v1NoSigB
				BitFail,
				eol2000c01v1NoSigBTrapEnable
				AlarmEnable,
				eol2000c01v1SfpPres
				Bit0Yes1No,
				eol2000c01v1SfpPresTrapEnable
				AlarmEnable,
				eol2000c01v1FailPtnDet
				BitFail,
				eol2000c01v1Grp1PresA
				Bit0No1Yes,
				eol2000c01v1Grp2PresA
				Bit0No1Yes,
				eol2000c01v1Grp3PresA
				Bit0No1Yes,
				eol2000c01v1Grp4PresA
				Bit0No1Yes,
				eol2000c01v1Grp1PresB
				Bit0No1Yes,
				eol2000c01v1Grp2PresB
				Bit0No1Yes,
				eol2000c01v1Grp3PresB
				Bit0No1Yes,
				eol2000c01v1Grp4PresB
				Bit0No1Yes,
				eol2000c01v1Grp1P0ErrA
				BitFail,
				eol2000c01v1Grp1P1ErrA
				BitFail,
				eol2000c01v1Grp2P0ErrA
				BitFail,
				eol2000c01v1Grp2P1ErrA
				BitFail,
				eol2000c01v1Grp3P0ErrA
				BitFail,
				eol2000c01v1Grp3P1ErrA
				BitFail,
				eol2000c01v1Grp4P0ErrA
				BitFail,
				eol2000c01v1Grp4P1ErrA
				BitFail,
				eol2000c01v1R2lIn1Pres
				BitFail,
				eol2000c01v1R2lIn2Pres
				BitFail,
				eol2000c01v1R2lIn3Pres
				BitFail,
				eol2000c01v1R2lIn4Pres
				BitFail,
				eol2000c01v1R2lIn5Pres
				BitFail,
				eol2000c01v1R2lIn6Pres
				BitFail,
				eol2000c01v1R2lIn7Pres
				BitFail,
				eol2000c01v1R2lIn8Pres
				BitFail,
				eol2000c01v1R2lIn9Pres
				BitFail,
				eol2000c01v1R2lIn10Pres
				BitFail,
				eol2000c01v1R2lIn11Pres
				BitFail,
				eol2000c01v1R2lIn12Pres
				BitFail,
				eol2000c01v1R2lIn13Pres
				BitFail,
				eol2000c01v1R2lIn14Pres
				BitFail,
				eol2000c01v1R2lIn15Pres
				BitFail,
				eol2000c01v1R2lIn16Pres
				BitFail,
				eol2000c01v1EthLink
				Ipa2EtherStat,
				eol2000c01v1EthSystem
				Ipa2EtherSys,
				eol2000c01v1Grp1P0ErrB
				BitFail,
				eol2000c01v1Grp1P1ErrB
				BitFail,
				eol2000c01v1Grp2P0ErrB
				BitFail,
				eol2000c01v1Grp2P1ErrB
				BitFail,
				eol2000c01v1Grp3P0ErrB
				BitFail,
				eol2000c01v1Grp3P1ErrB
				BitFail,
				eol2000c01v1Grp4P0ErrB
				BitFail,
				eol2000c01v1Grp4P1ErrB
				BitFail,
				eol2000c01v1RxPower
				OptPowerX2Uw,
				eol2000c01v1SerialNo
				SerialNo
			 }

		-- 1.3.6.1.4.1.10106.3.101291.1.1.1
		eol2000c01v1Index OBJECT-TYPE
			SYNTAX ModuleIndex
			MAX-ACCESS read-only
			STATUS current
			DESCRIPTION
				"Index of EOL2000C01V1 Table"
		::= { eol2000c01v1Entry 1 }

		-- 1.3.6.1.4.1.10106.3.101291.1.1.3
		eol2000c01v1GenlockMode OBJECT-TYPE
			SYNTAX Bit0Ele1Opt
			MAX-ACCESS read-write
			STATUS current
			DESCRIPTION
				"Allows selecting the reference input signal"
		::= { eol2000c01v1Entry 3 }

		-- 1.3.6.1.4.1.10106.3.101291.1.1.5
		eol2000c01v1Format OBJECT-TYPE
			SYNTAX SdiHd3gFmt6
			MAX-ACCESS read-write
			STATUS current
			DESCRIPTION
				"Output format for both sections"
		::= { eol2000c01v1Entry 5 }

		-- 1.3.6.1.4.1.10106.3.101291.1.1.7
		eol2000c01v1Bits OBJECT-TYPE
			SYNTAX Bit024120
			MAX-ACCESS read-write
			STATUS current
			DESCRIPTION
				"Allows selecting the number of bits"
		::= { eol2000c01v1Entry 7 }

		-- 1.3.6.1.4.1.10106.3.101291.1.1.9
		eol2000c01v1DeleteGr1 OBJECT-TYPE
			SYNTAX Bit0No1Yes
			MAX-ACCESS read-write
			STATUS current
			DESCRIPTION
				"Allows deleting group 1 audio packets"
		::= { eol2000c01v1Entry 9 }

		-- 1.3.6.1.4.1.10106.3.101291.1.1.11
		eol2000c01v1DeleteGr2 OBJECT-TYPE
			SYNTAX Bit0No1Yes
			MAX-ACCESS read-write
			STATUS current
			DESCRIPTION
				"Allows deleting group 2 audio packets"
		::= { eol2000c01v1Entry 11 }

		-- 1.3.6.1.4.1.10106.3.101291.1.1.13
		eol2000c01v1DeleteGr3 OBJECT-TYPE
			SYNTAX Bit0No1Yes
			MAX-ACCESS read-write
			STATUS current
			DESCRIPTION
				"Allows deleting group 3 audio packets"
		::= { eol2000c01v1Entry 13 }

		-- 1.3.6.1.4.1.10106.3.101291.1.1.15
		eol2000c01v1DeleteGr4 OBJECT-TYPE
			SYNTAX Bit0No1Yes
			MAX-ACCESS read-write
			STATUS current
			DESCRIPTION
				"Allows deleting group 4 audio packets"
		::= { eol2000c01v1Entry 15 }

		-- 1.3.6.1.4.1.10106.3.101291.1.1.17
		eol2000c01v1FreezeTout OBJECT-TYPE
			SYNTAX TimeS2
			MAX-ACCESS read-write
			STATUS current
			DESCRIPTION
				"Time spent transmitting a still frame in absence of a valid input (non-reference input only)"
		::= { eol2000c01v1Entry 17 }

		-- 1.3.6.1.4.1.10106.3.101291.1.1.19
		eol2000c01v1InFormat1 OBJECT-TYPE
			SYNTAX SdiHd3gFmt3
			MAX-ACCESS read-only
			STATUS current
			DESCRIPTION
				"SDI signal format"
		::= { eol2000c01v1Entry 19 }

		-- 1.3.6.1.4.1.10106.3.101291.1.1.20
		eol2000c01v1InFormat1TrapEnable OBJECT-TYPE
			SYNTAX AlarmEnable
			MAX-ACCESS read-write
			STATUS current
			DESCRIPTION
				"SDI signal format Trap Enable"
		::= { eol2000c01v1Entry 20 }

		-- 1.3.6.1.4.1.10106.3.101291.1.1.21
		eol2000c01v1InFormat2 OBJECT-TYPE
			SYNTAX SdiHd3gFmt3
			MAX-ACCESS read-only
			STATUS current
			DESCRIPTION
				"SDI signal format"
		::= { eol2000c01v1Entry 21 }

		-- 1.3.6.1.4.1.10106.3.101291.1.1.23
		eol2000c01v1RefUnlock OBJECT-TYPE
			SYNTAX BitFail
			MAX-ACCESS read-only
			STATUS current
			DESCRIPTION
				"Indicates reference signal unlock fail"
		::= { eol2000c01v1Entry 23 }

		-- 1.3.6.1.4.1.10106.3.101291.1.1.24
		eol2000c01v1RefUnlockTrapEnable OBJECT-TYPE
			SYNTAX AlarmEnable
			MAX-ACCESS read-write
			STATUS current
			DESCRIPTION
				"Indicates reference signal unlock fail Trap Enable"
		::= { eol2000c01v1Entry 24 }

		-- 1.3.6.1.4.1.10106.3.101291.1.1.25
		eol2000c01v1NoSigA OBJECT-TYPE
			SYNTAX BitFail
			MAX-ACCESS read-only
			STATUS current
			DESCRIPTION
				"Indicates SDI signal fail"
		::= { eol2000c01v1Entry 25 }

		-- 1.3.6.1.4.1.10106.3.101291.1.1.26
		eol2000c01v1NoSigATrapEnable OBJECT-TYPE
			SYNTAX AlarmEnable
			MAX-ACCESS read-write
			STATUS current
			DESCRIPTION
				"Indicates SDI signal fail Trap Enable"
		::= { eol2000c01v1Entry 26 }

		-- 1.3.6.1.4.1.10106.3.101291.1.1.27
		eol2000c01v1NoSigB OBJECT-TYPE
			SYNTAX BitFail
			MAX-ACCESS read-only
			STATUS current
			DESCRIPTION
				"Indicates SDI signal fail"
		::= { eol2000c01v1Entry 27 }

		-- 1.3.6.1.4.1.10106.3.101291.1.1.28
		eol2000c01v1NoSigBTrapEnable OBJECT-TYPE
			SYNTAX AlarmEnable
			MAX-ACCESS read-write
			STATUS current
			DESCRIPTION
				"Indicates SDI signal fail Trap Enable"
		::= { eol2000c01v1Entry 28 }

		-- 1.3.6.1.4.1.10106.3.101291.1.1.29
		eol2000c01v1SfpPres OBJECT-TYPE
			SYNTAX Bit0Yes1No
			MAX-ACCESS read-only
			STATUS current
			DESCRIPTION
				"Indicates whether a compatible SFP transceiver is present"
		::= { eol2000c01v1Entry 29 }

		-- 1.3.6.1.4.1.10106.3.101291.1.1.30
		eol2000c01v1SfpPresTrapEnable OBJECT-TYPE
			SYNTAX AlarmEnable
			MAX-ACCESS read-write
			STATUS current
			DESCRIPTION
				"Indicates whether a compatible SFP transceiver is present Trap Enable"
		::= { eol2000c01v1Entry 30 }

		-- 1.3.6.1.4.1.10106.3.101291.1.1.31
		eol2000c01v1FailPtnDet OBJECT-TYPE
			SYNTAX BitFail
			MAX-ACCESS read-only
			STATUS current
			DESCRIPTION
				"Input signal contains a pattern that indicates failure on the other side of the link"
		::= { eol2000c01v1Entry 31 }

		-- 1.3.6.1.4.1.10106.3.101291.1.1.33
		eol2000c01v1Grp1PresA OBJECT-TYPE
			SYNTAX Bit0No1Yes
			MAX-ACCESS read-only
			STATUS current
			DESCRIPTION
				"Group 1 presence"
		::= { eol2000c01v1Entry 33 }

		-- 1.3.6.1.4.1.10106.3.101291.1.1.35
		eol2000c01v1Grp2PresA OBJECT-TYPE
			SYNTAX Bit0No1Yes
			MAX-ACCESS read-only
			STATUS current
			DESCRIPTION
				"Group 2 presence"
		::= { eol2000c01v1Entry 35 }

		-- 1.3.6.1.4.1.10106.3.101291.1.1.37
		eol2000c01v1Grp3PresA OBJECT-TYPE
			SYNTAX Bit0No1Yes
			MAX-ACCESS read-only
			STATUS current
			DESCRIPTION
				"Group 3 presence"
		::= { eol2000c01v1Entry 37 }

		-- 1.3.6.1.4.1.10106.3.101291.1.1.39
		eol2000c01v1Grp4PresA OBJECT-TYPE
			SYNTAX Bit0No1Yes
			MAX-ACCESS read-only
			STATUS current
			DESCRIPTION
				"Group 4 presence"
		::= { eol2000c01v1Entry 39 }

		-- 1.3.6.1.4.1.10106.3.101291.1.1.41
		eol2000c01v1Grp1PresB OBJECT-TYPE
			SYNTAX Bit0No1Yes
			MAX-ACCESS read-only
			STATUS current
			DESCRIPTION
				"Group 1 presence"
		::= { eol2000c01v1Entry 41 }

		-- 1.3.6.1.4.1.10106.3.101291.1.1.43
		eol2000c01v1Grp2PresB OBJECT-TYPE
			SYNTAX Bit0No1Yes
			MAX-ACCESS read-only
			STATUS current
			DESCRIPTION
				"Group 2 presence"
		::= { eol2000c01v1Entry 43 }

		-- 1.3.6.1.4.1.10106.3.101291.1.1.45
		eol2000c01v1Grp3PresB OBJECT-TYPE
			SYNTAX Bit0No1Yes
			MAX-ACCESS read-only
			STATUS current
			DESCRIPTION
				"Group 3 presence"
		::= { eol2000c01v1Entry 45 }

		-- 1.3.6.1.4.1.10106.3.101291.1.1.47
		eol2000c01v1Grp4PresB OBJECT-TYPE
			SYNTAX Bit0No1Yes
			MAX-ACCESS read-only
			STATUS current
			DESCRIPTION
				"Group 4 presence"
		::= { eol2000c01v1Entry 47 }

		-- 1.3.6.1.4.1.10106.3.101291.1.1.49
		eol2000c01v1Grp1P0ErrA OBJECT-TYPE
			SYNTAX BitFail
			MAX-ACCESS read-only
			STATUS current
			DESCRIPTION
				"SDI group 1 pair 0 fail"
		::= { eol2000c01v1Entry 49 }

		-- 1.3.6.1.4.1.10106.3.101291.1.1.51
		eol2000c01v1Grp1P1ErrA OBJECT-TYPE
			SYNTAX BitFail
			MAX-ACCESS read-only
			STATUS current
			DESCRIPTION
				"SDI group 1 pair 1 fail"
		::= { eol2000c01v1Entry 51 }

		-- 1.3.6.1.4.1.10106.3.101291.1.1.53
		eol2000c01v1Grp2P0ErrA OBJECT-TYPE
			SYNTAX BitFail
			MAX-ACCESS read-only
			STATUS current
			DESCRIPTION
				"SDI group 2 pair 0 fail"
		::= { eol2000c01v1Entry 53 }

		-- 1.3.6.1.4.1.10106.3.101291.1.1.55
		eol2000c01v1Grp2P1ErrA OBJECT-TYPE
			SYNTAX BitFail
			MAX-ACCESS read-only
			STATUS current
			DESCRIPTION
				"SDI group 2 pair 1 fail"
		::= { eol2000c01v1Entry 55 }

		-- 1.3.6.1.4.1.10106.3.101291.1.1.57
		eol2000c01v1Grp3P0ErrA OBJECT-TYPE
			SYNTAX BitFail
			MAX-ACCESS read-only
			STATUS current
			DESCRIPTION
				"SDI group 3 pair 0 fail"
		::= { eol2000c01v1Entry 57 }

		-- 1.3.6.1.4.1.10106.3.101291.1.1.59
		eol2000c01v1Grp3P1ErrA OBJECT-TYPE
			SYNTAX BitFail
			MAX-ACCESS read-only
			STATUS current
			DESCRIPTION
				"SDI group 3 pair 1 fail"
		::= { eol2000c01v1Entry 59 }

		-- 1.3.6.1.4.1.10106.3.101291.1.1.61
		eol2000c01v1Grp4P0ErrA OBJECT-TYPE
			SYNTAX BitFail
			MAX-ACCESS read-only
			STATUS current
			DESCRIPTION
				"SDI group 4 pair 0 fail"
		::= { eol2000c01v1Entry 61 }

		-- 1.3.6.1.4.1.10106.3.101291.1.1.63
		eol2000c01v1Grp4P1ErrA OBJECT-TYPE
			SYNTAX BitFail
			MAX-ACCESS read-only
			STATUS current
			DESCRIPTION
				"SDI group 4 pair 1 fail"
		::= { eol2000c01v1Entry 63 }

		-- 1.3.6.1.4.1.10106.3.101291.1.1.65
		eol2000c01v1R2lIn1Pres OBJECT-TYPE
			SYNTAX BitFail
			MAX-ACCESS read-only
			STATUS current
			DESCRIPTION
				"R2L IN channel 1 fail"
		::= { eol2000c01v1Entry 65 }

		-- 1.3.6.1.4.1.10106.3.101291.1.1.67
		eol2000c01v1R2lIn2Pres OBJECT-TYPE
			SYNTAX BitFail
			MAX-ACCESS read-only
			STATUS current
			DESCRIPTION
				"R2L IN channel 2 fail"
		::= { eol2000c01v1Entry 67 }

		-- 1.3.6.1.4.1.10106.3.101291.1.1.69
		eol2000c01v1R2lIn3Pres OBJECT-TYPE
			SYNTAX BitFail
			MAX-ACCESS read-only
			STATUS current
			DESCRIPTION
				"R2L IN channel 3 fail"
		::= { eol2000c01v1Entry 69 }

		-- 1.3.6.1.4.1.10106.3.101291.1.1.71
		eol2000c01v1R2lIn4Pres OBJECT-TYPE
			SYNTAX BitFail
			MAX-ACCESS read-only
			STATUS current
			DESCRIPTION
				"R2L IN channel 4 fail"
		::= { eol2000c01v1Entry 71 }

		-- 1.3.6.1.4.1.10106.3.101291.1.1.73
		eol2000c01v1R2lIn5Pres OBJECT-TYPE
			SYNTAX BitFail
			MAX-ACCESS read-only
			STATUS current
			DESCRIPTION
				"R2L IN channel 5 fail"
		::= { eol2000c01v1Entry 73 }

		-- 1.3.6.1.4.1.10106.3.101291.1.1.75
		eol2000c01v1R2lIn6Pres OBJECT-TYPE
			SYNTAX BitFail
			MAX-ACCESS read-only
			STATUS current
			DESCRIPTION
				"R2L IN channel 6 fail"
		::= { eol2000c01v1Entry 75 }

		-- 1.3.6.1.4.1.10106.3.101291.1.1.77
		eol2000c01v1R2lIn7Pres OBJECT-TYPE
			SYNTAX BitFail
			MAX-ACCESS read-only
			STATUS current
			DESCRIPTION
				"R2L IN channel 7 fail"
		::= { eol2000c01v1Entry 77 }

		-- 1.3.6.1.4.1.10106.3.101291.1.1.79
		eol2000c01v1R2lIn8Pres OBJECT-TYPE
			SYNTAX BitFail
			MAX-ACCESS read-only
			STATUS current
			DESCRIPTION
				"R2L IN channel 8 fail"
		::= { eol2000c01v1Entry 79 }

		-- 1.3.6.1.4.1.10106.3.101291.1.1.81
		eol2000c01v1R2lIn9Pres OBJECT-TYPE
			SYNTAX BitFail
			MAX-ACCESS read-only
			STATUS current
			DESCRIPTION
				"R2L IN channel 9 fail"
		::= { eol2000c01v1Entry 81 }

		-- 1.3.6.1.4.1.10106.3.101291.1.1.83
		eol2000c01v1R2lIn10Pres OBJECT-TYPE
			SYNTAX BitFail
			MAX-ACCESS read-only
			STATUS current
			DESCRIPTION
				"R2L IN channel 10 fail"
		::= { eol2000c01v1Entry 83 }

		-- 1.3.6.1.4.1.10106.3.101291.1.1.85
		eol2000c01v1R2lIn11Pres OBJECT-TYPE
			SYNTAX BitFail
			MAX-ACCESS read-only
			STATUS current
			DESCRIPTION
				"R2L IN channel 11 fail"
		::= { eol2000c01v1Entry 85 }

		-- 1.3.6.1.4.1.10106.3.101291.1.1.87
		eol2000c01v1R2lIn12Pres OBJECT-TYPE
			SYNTAX BitFail
			MAX-ACCESS read-only
			STATUS current
			DESCRIPTION
				"R2L IN channel 12 fail"
		::= { eol2000c01v1Entry 87 }

		-- 1.3.6.1.4.1.10106.3.101291.1.1.89
		eol2000c01v1R2lIn13Pres OBJECT-TYPE
			SYNTAX BitFail
			MAX-ACCESS read-only
			STATUS current
			DESCRIPTION
				"R2L IN channel 13 fail"
		::= { eol2000c01v1Entry 89 }

		-- 1.3.6.1.4.1.10106.3.101291.1.1.91
		eol2000c01v1R2lIn14Pres OBJECT-TYPE
			SYNTAX BitFail
			MAX-ACCESS read-only
			STATUS current
			DESCRIPTION
				"R2L IN channel 14 fail"
		::= { eol2000c01v1Entry 91 }

		-- 1.3.6.1.4.1.10106.3.101291.1.1.93
		eol2000c01v1R2lIn15Pres OBJECT-TYPE
			SYNTAX BitFail
			MAX-ACCESS read-only
			STATUS current
			DESCRIPTION
				"R2L IN channel 15 fail"
		::= { eol2000c01v1Entry 93 }

		-- 1.3.6.1.4.1.10106.3.101291.1.1.95
		eol2000c01v1R2lIn16Pres OBJECT-TYPE
			SYNTAX BitFail
			MAX-ACCESS read-only
			STATUS current
			DESCRIPTION
				"R2L IN channel 16 fail"
		::= { eol2000c01v1Entry 95 }

		-- 1.3.6.1.4.1.10106.3.101291.1.1.97
		eol2000c01v1EthLink OBJECT-TYPE
			SYNTAX Ipa2EtherStat
			MAX-ACCESS read-only
			STATUS current
			DESCRIPTION
				"Ethernet conection status"
		::= { eol2000c01v1Entry 97 }

		-- 1.3.6.1.4.1.10106.3.101291.1.1.99
		eol2000c01v1EthSystem OBJECT-TYPE
			SYNTAX Ipa2EtherSys
			MAX-ACCESS read-only
			STATUS current
			DESCRIPTION
				"Ethernet conection system"
		::= { eol2000c01v1Entry 99 }

		-- 1.3.6.1.4.1.10106.3.101291.1.1.101
		eol2000c01v1Grp1P0ErrB OBJECT-TYPE
			SYNTAX BitFail
			MAX-ACCESS read-only
			STATUS current
			DESCRIPTION
				"SDI group 1 pair 0 fail"
		::= { eol2000c01v1Entry 101 }

		-- 1.3.6.1.4.1.10106.3.101291.1.1.103
		eol2000c01v1Grp1P1ErrB OBJECT-TYPE
			SYNTAX BitFail
			MAX-ACCESS read-only
			STATUS current
			DESCRIPTION
				"SDI group 1 pair 1 fail"
		::= { eol2000c01v1Entry 103 }

		-- 1.3.6.1.4.1.10106.3.101291.1.1.105
		eol2000c01v1Grp2P0ErrB OBJECT-TYPE
			SYNTAX BitFail
			MAX-ACCESS read-only
			STATUS current
			DESCRIPTION
				"SDI group 2 pair 0 fail"
		::= { eol2000c01v1Entry 105 }

		-- 1.3.6.1.4.1.10106.3.101291.1.1.107
		eol2000c01v1Grp2P1ErrB OBJECT-TYPE
			SYNTAX BitFail
			MAX-ACCESS read-only
			STATUS current
			DESCRIPTION
				"SDI group 2 pair 1 fail"
		::= { eol2000c01v1Entry 107 }

		-- 1.3.6.1.4.1.10106.3.101291.1.1.109
		eol2000c01v1Grp3P0ErrB OBJECT-TYPE
			SYNTAX BitFail
			MAX-ACCESS read-only
			STATUS current
			DESCRIPTION
				"SDI group 3 pair 0 fail"
		::= { eol2000c01v1Entry 109 }

		-- 1.3.6.1.4.1.10106.3.101291.1.1.111
		eol2000c01v1Grp3P1ErrB OBJECT-TYPE
			SYNTAX BitFail
			MAX-ACCESS read-only
			STATUS current
			DESCRIPTION
				"SDI group 3 pair 1 fail"
		::= { eol2000c01v1Entry 111 }

		-- 1.3.6.1.4.1.10106.3.101291.1.1.113
		eol2000c01v1Grp4P0ErrB OBJECT-TYPE
			SYNTAX BitFail
			MAX-ACCESS read-only
			STATUS current
			DESCRIPTION
				"SDI group 4 pair 0 fail"
		::= { eol2000c01v1Entry 113 }

		-- 1.3.6.1.4.1.10106.3.101291.1.1.115
		eol2000c01v1Grp4P1ErrB OBJECT-TYPE
			SYNTAX BitFail
			MAX-ACCESS read-only
			STATUS current
			DESCRIPTION
				"SDI group 4 pair 1 fail"
		::= { eol2000c01v1Entry 115 }

		-- 1.3.6.1.4.1.10106.3.101291.1.1.117
		eol2000c01v1RxPower OBJECT-TYPE
			SYNTAX OptPowerX2Uw
			MAX-ACCESS read-only
			STATUS current
			DESCRIPTION
				"Optical received power"
		::= { eol2000c01v1Entry 117 }

		-- 1.3.6.1.4.1.10106.3.101291.1.1.119
		eol2000c01v1SerialNo OBJECT-TYPE
			SYNTAX SerialNo
			MAX-ACCESS read-only
			STATUS current
			DESCRIPTION
				"Serial number"
		::= { eol2000c01v1Entry 119 }

		-- 1.3.6.1.4.1.10106.3.529001
		ttd2000c01v1 OBJECT IDENTIFIER ::= { albalaProducts 529001 }

		-- 1.3.6.1.4.1.10106.3.529001.1
		ttd2000c01v1Table  OBJECT-TYPE
			SYNTAX SEQUENCE OF Ttd2000c01v1Entry
			MAX-ACCESS not-accessible
			STATUS current
			DESCRIPTION
				"Module  TTD2000C01V1 Table"
			::= { ttd2000c01v1 1 }

		-- 1.3.6.1.4.1.10106.3.529001.1.1
		ttd2000c01v1Entry  OBJECT-TYPE
			SYNTAX Ttd2000c01v1Entry
			MAX-ACCESS not-accessible
			STATUS current
			DESCRIPTION
				"Module TTD2000C01V1 Entry"
			INDEX { ttd2000c01v1Index }
			::= { ttd2000c01v1Table 1 }

			Ttd2000c01v1Entry ::=
			SEQUENCE {
				ttd2000c01v1Index
				ModuleIndex,
				ttd2000c01v1FrInput
				Ttd2Input,
				ttd2000c01v1FrInputTrapEnable
				AlarmEnable,
				ttd2000c01v1Onepps12
				Ttd2OutSel,
				ttd2000c01v1Onepps12TrapEnable
				AlarmEnable,
				ttd2000c01v1Onepps34
				Ttd2OutSel,
				ttd2000c01v1Onepps34TrapEnable
				AlarmEnable,
				ttd2000c01v1Impedance
				Impedance,
				ttd2000c01v1ForceTtlOut
				BitMask,
				ttd2000c01v1FrFail
				BitFail,
				ttd2000c01v1FrFailTrapEnable
				AlarmEnable,
				ttd2000c01v1ReTtlFail
				BitFail,
				ttd2000c01v1ReTtlFailTrapEnable
				AlarmEnable,
				ttd2000c01v1Re10mhzFail
				BitFail,
				ttd2000c01v1Re10mhzFailTrapEnable
				AlarmEnable,
				ttd2000c01v1SerialNo
				SerialNo
			 }

		-- 1.3.6.1.4.1.10106.3.101291.1.1.1
		ttd2000c01v1Index OBJECT-TYPE
			SYNTAX ModuleIndex
			MAX-ACCESS read-only
			STATUS current
			DESCRIPTION
				"Index of TTD2000C01V1 Table"
		::= { ttd2000c01v1Entry 1 }

		-- 1.3.6.1.4.1.10106.3.101291.1.1.3
		ttd2000c01v1FrInput OBJECT-TYPE
			SYNTAX Ttd2Input
			MAX-ACCESS read-write
			STATUS current
			DESCRIPTION
				"Selected input"
		::= { ttd2000c01v1Entry 3 }

		-- 1.3.6.1.4.1.10106.3.101291.1.1.4
		ttd2000c01v1FrInputTrapEnable OBJECT-TYPE
			SYNTAX AlarmEnable
			MAX-ACCESS read-write
			STATUS current
			DESCRIPTION
				"Selected input Trap Enable"
		::= { ttd2000c01v1Entry 4 }

		-- 1.3.6.1.4.1.10106.3.101291.1.1.5
		ttd2000c01v1Onepps12 OBJECT-TYPE
			SYNTAX Ttd2OutSel
			MAX-ACCESS read-write
			STATUS current
			DESCRIPTION
				"Allows selecting the signal delivered to outputs 1 & 2"
		::= { ttd2000c01v1Entry 5 }

		-- 1.3.6.1.4.1.10106.3.101291.1.1.6
		ttd2000c01v1Onepps12TrapEnable OBJECT-TYPE
			SYNTAX AlarmEnable
			MAX-ACCESS read-write
			STATUS current
			DESCRIPTION
				"Allows selecting the signal delivered to outputs 1 & 2 Trap Enable"
		::= { ttd2000c01v1Entry 6 }

		-- 1.3.6.1.4.1.10106.3.101291.1.1.7
		ttd2000c01v1Onepps34 OBJECT-TYPE
			SYNTAX Ttd2OutSel
			MAX-ACCESS read-write
			STATUS current
			DESCRIPTION
				"4  & 5"
		::= { ttd2000c01v1Entry 7 }

		-- 1.3.6.1.4.1.10106.3.101291.1.1.8
		ttd2000c01v1Onepps34TrapEnable OBJECT-TYPE
			SYNTAX AlarmEnable
			MAX-ACCESS read-write
			STATUS current
			DESCRIPTION
				"4  & 5 Trap Enable"
		::= { ttd2000c01v1Entry 8 }

		-- 1.3.6.1.4.1.10106.3.101291.1.1.9
		ttd2000c01v1Impedance OBJECT-TYPE
			SYNTAX Impedance
			MAX-ACCESS read-write
			STATUS current
			DESCRIPTION
				"Allows selecting the input/output impedance"
		::= { ttd2000c01v1Entry 9 }

		-- 1.3.6.1.4.1.10106.3.101291.1.1.11
		ttd2000c01v1ForceTtlOut OBJECT-TYPE
			SYNTAX BitMask
			MAX-ACCESS read-write
			STATUS current
			DESCRIPTION
				"Allows forcing TTL levels at the outputs"
		::= { ttd2000c01v1Entry 11 }

		-- 1.3.6.1.4.1.10106.3.101291.1.1.13
		ttd2000c01v1FrFail OBJECT-TYPE
			SYNTAX BitFail
			MAX-ACCESS read-only
			STATUS current
			DESCRIPTION
				"Indicates front input signal fail"
		::= { ttd2000c01v1Entry 13 }

		-- 1.3.6.1.4.1.10106.3.101291.1.1.14
		ttd2000c01v1FrFailTrapEnable OBJECT-TYPE
			SYNTAX AlarmEnable
			MAX-ACCESS read-write
			STATUS current
			DESCRIPTION
				"Indicates front input signal fail Trap Enable"
		::= { ttd2000c01v1Entry 14 }

		-- 1.3.6.1.4.1.10106.3.101291.1.1.15
		ttd2000c01v1ReTtlFail OBJECT-TYPE
			SYNTAX BitFail
			MAX-ACCESS read-only
			STATUS current
			DESCRIPTION
				"Indicates 1 PPS/48 kHz bus signal fail"
		::= { ttd2000c01v1Entry 15 }

		-- 1.3.6.1.4.1.10106.3.101291.1.1.16
		ttd2000c01v1ReTtlFailTrapEnable OBJECT-TYPE
			SYNTAX AlarmEnable
			MAX-ACCESS read-write
			STATUS current
			DESCRIPTION
				"Indicates 1 PPS/48 kHz bus signal fail Trap Enable"
		::= { ttd2000c01v1Entry 16 }

		-- 1.3.6.1.4.1.10106.3.101291.1.1.17
		ttd2000c01v1Re10mhzFail OBJECT-TYPE
			SYNTAX BitFail
			MAX-ACCESS read-only
			STATUS current
			DESCRIPTION
				"Indicates 10 MHz bus signal fail"
		::= { ttd2000c01v1Entry 17 }

		-- 1.3.6.1.4.1.10106.3.101291.1.1.18
		ttd2000c01v1Re10mhzFailTrapEnable OBJECT-TYPE
			SYNTAX AlarmEnable
			MAX-ACCESS read-write
			STATUS current
			DESCRIPTION
				"Indicates 10 MHz bus signal fail Trap Enable"
		::= { ttd2000c01v1Entry 18 }

		-- 1.3.6.1.4.1.10106.3.101291.1.1.19
		ttd2000c01v1SerialNo OBJECT-TYPE
			SYNTAX SerialNo
			MAX-ACCESS read-only
			STATUS current
			DESCRIPTION
				"Serial number"
		::= { ttd2000c01v1Entry 19 }

		-- 1.3.6.1.4.1.10106.3.530801
		psu2100c01v1 OBJECT IDENTIFIER ::= { albalaProducts 530801 }

		-- 1.3.6.1.4.1.10106.3.530801.1
		psu2100c01v1Table  OBJECT-TYPE
			SYNTAX SEQUENCE OF Psu2100c01v1Entry
			MAX-ACCESS not-accessible
			STATUS current
			DESCRIPTION
				"Module  PSU2100C01V1 Table"
			::= { psu2100c01v1 1 }

		-- 1.3.6.1.4.1.10106.3.530801.1.1
		psu2100c01v1Entry  OBJECT-TYPE
			SYNTAX Psu2100c01v1Entry
			MAX-ACCESS not-accessible
			STATUS current
			DESCRIPTION
				"Module PSU2100C01V1 Entry"
			INDEX { psu2100c01v1Index }
			::= { psu2100c01v1Table 1 }

			Psu2100c01v1Entry ::=
			SEQUENCE {
				psu2100c01v1Index
				ModuleIndex,
				psu2100c01v1PowerOff
				BitFail,
				psu2100c01v1PowerOffTrapEnable
				AlarmEnable,
				psu2100c01v1TempWarning
				BitFail,
				psu2100c01v1TempWarningTrapEnable
				AlarmEnable,
				psu2100c01v1TempFail
				BitFail,
				psu2100c01v1TempFailTrapEnable
				AlarmEnable,
				psu2100c01v1PwrWarning
				BitFail,
				psu2100c01v1PwrWarningTrapEnable
				AlarmEnable,
				psu2100c01v1PwrFail
				BitFail,
				psu2100c01v1PwrFailTrapEnable
				AlarmEnable,
				psu2100c01v1InputVolt
				PsuDcInpV,
				psu2100c01v1OutputPower
				PowerX1W,
				psu2100c01v1ActTemp
				Temperature0c1,
				psu2100c01v1MeanTemp
				Temperature0c1,
				psu2100c01v1MaxTemp
				Temperature0c1,
				psu2100c01v1PonHours
				TimeX1Hour,
				psu2100c01v1TotMaxTemp
				Temperature0c1,
				psu2100c01v1TotPonHours
				TimeX1Hour,
				psu2100c01v1TotPonTimes
				Uint16,
				psu2100c01v1SerialNo
				SerialNo
			 }

		-- 1.3.6.1.4.1.10106.3.101291.1.1.1
		psu2100c01v1Index OBJECT-TYPE
			SYNTAX ModuleIndex
			MAX-ACCESS read-only
			STATUS current
			DESCRIPTION
				"Index of PSU2100C01V1 Table"
		::= { psu2100c01v1Entry 1 }

		-- 1.3.6.1.4.1.10106.3.101291.1.1.3
		psu2100c01v1PowerOff OBJECT-TYPE
			SYNTAX BitFail
			MAX-ACCESS read-only
			STATUS current
			DESCRIPTION
				"Indicates the power supply status"
		::= { psu2100c01v1Entry 3 }

		-- 1.3.6.1.4.1.10106.3.101291.1.1.4
		psu2100c01v1PowerOffTrapEnable OBJECT-TYPE
			SYNTAX AlarmEnable
			MAX-ACCESS read-write
			STATUS current
			DESCRIPTION
				"Indicates the power supply status Trap Enable"
		::= { psu2100c01v1Entry 4 }

		-- 1.3.6.1.4.1.10106.3.101291.1.1.5
		psu2100c01v1TempWarning OBJECT-TYPE
			SYNTAX BitFail
			MAX-ACCESS read-only
			STATUS current
			DESCRIPTION
				"Indicates that actual temperature is over expected range"
		::= { psu2100c01v1Entry 5 }

		-- 1.3.6.1.4.1.10106.3.101291.1.1.6
		psu2100c01v1TempWarningTrapEnable OBJECT-TYPE
			SYNTAX AlarmEnable
			MAX-ACCESS read-write
			STATUS current
			DESCRIPTION
				"Indicates that actual temperature is over expected range Trap Enable"
		::= { psu2100c01v1Entry 6 }

		-- 1.3.6.1.4.1.10106.3.101291.1.1.7
		psu2100c01v1TempFail OBJECT-TYPE
			SYNTAX BitFail
			MAX-ACCESS read-only
			STATUS current
			DESCRIPTION
				"Indicates that actual temperature is over recommended range"
		::= { psu2100c01v1Entry 7 }

		-- 1.3.6.1.4.1.10106.3.101291.1.1.8
		psu2100c01v1TempFailTrapEnable OBJECT-TYPE
			SYNTAX AlarmEnable
			MAX-ACCESS read-write
			STATUS current
			DESCRIPTION
				"Indicates that actual temperature is over recommended range Trap Enable"
		::= { psu2100c01v1Entry 8 }

		-- 1.3.6.1.4.1.10106.3.101291.1.1.9
		psu2100c01v1PwrWarning OBJECT-TYPE
			SYNTAX BitFail
			MAX-ACCESS read-only
			STATUS current
			DESCRIPTION
				"Indicates that actual output power is over expected range"
		::= { psu2100c01v1Entry 9 }

		-- 1.3.6.1.4.1.10106.3.101291.1.1.10
		psu2100c01v1PwrWarningTrapEnable OBJECT-TYPE
			SYNTAX AlarmEnable
			MAX-ACCESS read-write
			STATUS current
			DESCRIPTION
				"Indicates that actual output power is over expected range Trap Enable"
		::= { psu2100c01v1Entry 10 }

		-- 1.3.6.1.4.1.10106.3.101291.1.1.11
		psu2100c01v1PwrFail OBJECT-TYPE
			SYNTAX BitFail
			MAX-ACCESS read-only
			STATUS current
			DESCRIPTION
				"Indicates that actual output power is over allowed range"
		::= { psu2100c01v1Entry 11 }

		-- 1.3.6.1.4.1.10106.3.101291.1.1.12
		psu2100c01v1PwrFailTrapEnable OBJECT-TYPE
			SYNTAX AlarmEnable
			MAX-ACCESS read-write
			STATUS current
			DESCRIPTION
				"Indicates that actual output power is over allowed range Trap Enable"
		::= { psu2100c01v1Entry 12 }

		-- 1.3.6.1.4.1.10106.3.101291.1.1.13
		psu2100c01v1InputVolt OBJECT-TYPE
			SYNTAX PsuDcInpV
			MAX-ACCESS read-only
			STATUS current
			DESCRIPTION
				"Displays the DC input voltaje"
		::= { psu2100c01v1Entry 13 }

		-- 1.3.6.1.4.1.10106.3.101291.1.1.15
		psu2100c01v1OutputPower OBJECT-TYPE
			SYNTAX PowerX1W
			MAX-ACCESS read-only
			STATUS current
			DESCRIPTION
				"Displays the delivered output power"
		::= { psu2100c01v1Entry 15 }

		-- 1.3.6.1.4.1.10106.3.101291.1.1.17
		psu2100c01v1ActTemp OBJECT-TYPE
			SYNTAX Temperature0c1
			MAX-ACCESS read-only
			STATUS current
			DESCRIPTION
				"Displays internal actual temperature"
		::= { psu2100c01v1Entry 17 }

		-- 1.3.6.1.4.1.10106.3.101291.1.1.19
		psu2100c01v1MeanTemp OBJECT-TYPE
			SYNTAX Temperature0c1
			MAX-ACCESS read-only
			STATUS current
			DESCRIPTION
				"Displays internal mean temperature"
		::= { psu2100c01v1Entry 19 }

		-- 1.3.6.1.4.1.10106.3.101291.1.1.21
		psu2100c01v1MaxTemp OBJECT-TYPE
			SYNTAX Temperature0c1
			MAX-ACCESS read-only
			STATUS current
			DESCRIPTION
				"Displays internal maximun temperature"
		::= { psu2100c01v1Entry 21 }

		-- 1.3.6.1.4.1.10106.3.101291.1.1.23
		psu2100c01v1PonHours OBJECT-TYPE
			SYNTAX TimeX1Hour
			MAX-ACCESS read-only
			STATUS current
			DESCRIPTION
				"Displays module power on time"
		::= { psu2100c01v1Entry 23 }

		-- 1.3.6.1.4.1.10106.3.101291.1.1.25
		psu2100c01v1TotMaxTemp OBJECT-TYPE
			SYNTAX Temperature0c1
			MAX-ACCESS read-only
			STATUS current
			DESCRIPTION
				"Displays internal maximun tempertature since first power on"
		::= { psu2100c01v1Entry 25 }

		-- 1.3.6.1.4.1.10106.3.101291.1.1.27
		psu2100c01v1TotPonHours OBJECT-TYPE
			SYNTAX TimeX1Hour
			MAX-ACCESS read-only
			STATUS current
			DESCRIPTION
				"Displays module power on time since first power on"
		::= { psu2100c01v1Entry 27 }

		-- 1.3.6.1.4.1.10106.3.101291.1.1.29
		psu2100c01v1TotPonTimes OBJECT-TYPE
			SYNTAX Uint16
			MAX-ACCESS read-only
			STATUS current
			DESCRIPTION
				"Displays module power on events since first power on"
		::= { psu2100c01v1Entry 29 }

		-- 1.3.6.1.4.1.10106.3.101291.1.1.31
		psu2100c01v1SerialNo OBJECT-TYPE
			SYNTAX SerialNo
			MAX-ACCESS read-only
			STATUS current
			DESCRIPTION
				"Serial number"
		::= { psu2100c01v1Entry 31 }

		-- 1.3.6.1.4.1.10106.3.538901
		atg2000c01v1 OBJECT IDENTIFIER ::= { albalaProducts 538901 }

		-- 1.3.6.1.4.1.10106.3.538901.1
		atg2000c01v1Table  OBJECT-TYPE
			SYNTAX SEQUENCE OF Atg2000c01v1Entry
			MAX-ACCESS not-accessible
			STATUS current
			DESCRIPTION
				"Module  ATG2000C01V1 Table"
			::= { atg2000c01v1 1 }

		-- 1.3.6.1.4.1.10106.3.538901.1.1
		atg2000c01v1Entry  OBJECT-TYPE
			SYNTAX Atg2000c01v1Entry
			MAX-ACCESS not-accessible
			STATUS current
			DESCRIPTION
				"Module ATG2000C01V1 Entry"
			INDEX { atg2000c01v1Index }
			::= { atg2000c01v1Table 1 }

			Atg2000c01v1Entry ::=
			SEQUENCE {
				atg2000c01v1Index
				ModuleIndex,
				atg2000c01v1ActivePreset
				Preset16Active,
				atg2000c01v1LoadPreset
				Preset16Load,
				atg2000c01v1SavePreset
				Preset16Save,
				atg2000c01v1LtcFormat
				Bit029fr125f,
				atg2000c01v1MuxSrc2
				AtgMuxSrc,
				atg2000c01v1AudFr
				AudioFreq1,
				atg2000c01v1AudDip
				Bit0Dis1Ena,
				atg2000c01v1AudLev
				AudioLev0,
				atg2000c01v1SampRate
				AudioSelFreq7,
				atg2000c01v1DropFrame
				BitMask,
				atg2000c01v1Bgf
				BgfBits,
				atg2000c01v1DateFormat
				DateFmt,
				atg2000c01v1EnDateGen
				BitMask,
				atg2000c01v1SumMonthSt
				Month,
				atg2000c01v1SumWeekSt
				WeekOfMonth,
				atg2000c01v1SumWDaySt
				Day,
				atg2000c01v1SumHourSt
				TimeH1,
				atg2000c01v1SumHourOffset
				Int8,
				atg2000c01v1WinMonthSt
				Month,
				atg2000c01v1WinWeekSt
				WeekOfMonth,
				atg2000c01v1WinWDaySt
				Day,
				atg2000c01v1WinHourSt
				TimeH1,
				atg2000c01v1WinHourOffset
				Int8,
				atg2000c01v1EnDlsave
				BitMask,
				atg2000c01v1RefLockFail
				BitFail,
				atg2000c01v1RefLockFailTrapEnable
				AlarmEnable,
				atg2000c01v1TcFail
				BitFail,
				atg2000c01v1RefPresentFail
				BitFail,
				atg2000c01v1SerialNo
				SerialNo
			 }

		-- 1.3.6.1.4.1.10106.3.101291.1.1.1
		atg2000c01v1Index OBJECT-TYPE
			SYNTAX ModuleIndex
			MAX-ACCESS read-only
			STATUS current
			DESCRIPTION
				"Index of ATG2000C01V1 Table"
		::= { atg2000c01v1Entry 1 }

		-- 1.3.6.1.4.1.10106.3.101291.1.1.3
		atg2000c01v1ActivePreset OBJECT-TYPE
			SYNTAX Preset16Active
			MAX-ACCESS read-only
			STATUS current
			DESCRIPTION
				"Shows the active preset"
		::= { atg2000c01v1Entry 3 }

		-- 1.3.6.1.4.1.10106.3.101291.1.1.5
		atg2000c01v1LoadPreset OBJECT-TYPE
			SYNTAX Preset16Load
			MAX-ACCESS read-write
			STATUS current
			DESCRIPTION
				"Allows loading a preset"
		::= { atg2000c01v1Entry 5 }

		-- 1.3.6.1.4.1.10106.3.101291.1.1.7
		atg2000c01v1SavePreset OBJECT-TYPE
			SYNTAX Preset16Save
			MAX-ACCESS read-write
			STATUS current
			DESCRIPTION
				"Allows saving a preset"
		::= { atg2000c01v1Entry 7 }

		-- 1.3.6.1.4.1.10106.3.101291.1.1.9
		atg2000c01v1LtcFormat OBJECT-TYPE
			SYNTAX Bit029fr125f
			MAX-ACCESS read-write
			STATUS current
			DESCRIPTION
				"LTC output format"
		::= { atg2000c01v1Entry 9 }

		-- 1.3.6.1.4.1.10106.3.101291.1.1.11
		atg2000c01v1MuxSrc2 OBJECT-TYPE
			SYNTAX AtgMuxSrc
			MAX-ACCESS read-write
			STATUS current
			DESCRIPTION
				"Source generator for time info outputs"
		::= { atg2000c01v1Entry 11 }

		-- 1.3.6.1.4.1.10106.3.101291.1.1.13
		atg2000c01v1AudFr OBJECT-TYPE
			SYNTAX AudioFreq1
			MAX-ACCESS read-write
			STATUS current
			DESCRIPTION
				"Tone generator frequency"
		::= { atg2000c01v1Entry 13 }

		-- 1.3.6.1.4.1.10106.3.101291.1.1.15
		atg2000c01v1AudDip OBJECT-TYPE
			SYNTAX Bit0Dis1Ena
			MAX-ACCESS read-write
			STATUS current
			DESCRIPTION
				"Enables silence insertion for channel identification"
		::= { atg2000c01v1Entry 15 }

		-- 1.3.6.1.4.1.10106.3.101291.1.1.17
		atg2000c01v1AudLev OBJECT-TYPE
			SYNTAX AudioLev0
			MAX-ACCESS read-write
			STATUS current
			DESCRIPTION
				"Allows selecting the audio level for tone generation"
		::= { atg2000c01v1Entry 17 }

		-- 1.3.6.1.4.1.10106.3.101291.1.1.19
		atg2000c01v1SampRate OBJECT-TYPE
			SYNTAX AudioSelFreq7
			MAX-ACCESS read-write
			STATUS current
			DESCRIPTION
				"Sampling frequency used by AES and wordclock outputs"
		::= { atg2000c01v1Entry 19 }

		-- 1.3.6.1.4.1.10106.3.101291.1.1.21
		atg2000c01v1DropFrame OBJECT-TYPE
			SYNTAX BitMask
			MAX-ACCESS read-write
			STATUS current
			DESCRIPTION
				"Enables time compensated mode in 525-line LTC"
		::= { atg2000c01v1Entry 21 }

		-- 1.3.6.1.4.1.10106.3.101291.1.1.23
		atg2000c01v1Bgf OBJECT-TYPE
			SYNTAX BgfBits
			MAX-ACCESS read-write
			STATUS current
			DESCRIPTION
				"Contents of the binary group flags in the time code"
		::= { atg2000c01v1Entry 23 }

		-- 1.3.6.1.4.1.10106.3.101291.1.1.25
		atg2000c01v1DateFormat OBJECT-TYPE
			SYNTAX DateFmt
			MAX-ACCESS read-write
			STATUS current
			DESCRIPTION
				"Selects date format in the BGF (binary group flags)"
		::= { atg2000c01v1Entry 25 }

		-- 1.3.6.1.4.1.10106.3.101291.1.1.27
		atg2000c01v1EnDateGen OBJECT-TYPE
			SYNTAX BitMask
			MAX-ACCESS read-write
			STATUS current
			DESCRIPTION
				"Enables date insertion in time code"
		::= { atg2000c01v1Entry 27 }

		-- 1.3.6.1.4.1.10106.3.101291.1.1.29
		atg2000c01v1SumMonthSt OBJECT-TYPE
			SYNTAX Month
			MAX-ACCESS read-write
			STATUS current
			DESCRIPTION
				"It allows selecting the month when summer time starts"
		::= { atg2000c01v1Entry 29 }

		-- 1.3.6.1.4.1.10106.3.101291.1.1.31
		atg2000c01v1SumWeekSt OBJECT-TYPE
			SYNTAX WeekOfMonth
			MAX-ACCESS read-write
			STATUS current
			DESCRIPTION
				"It allows selecting the week of the month when summer time starts"
		::= { atg2000c01v1Entry 31 }

		-- 1.3.6.1.4.1.10106.3.101291.1.1.33
		atg2000c01v1SumWDaySt OBJECT-TYPE
			SYNTAX Day
			MAX-ACCESS read-write
			STATUS current
			DESCRIPTION
				"It allows selecting the week day when summer time starts"
		::= { atg2000c01v1Entry 33 }

		-- 1.3.6.1.4.1.10106.3.101291.1.1.35
		atg2000c01v1SumHourSt OBJECT-TYPE
			SYNTAX TimeH1
			MAX-ACCESS read-write
			STATUS current
			DESCRIPTION
				"It allows selecting the UTC hour when summer time starts"
		::= { atg2000c01v1Entry 35 }

		-- 1.3.6.1.4.1.10106.3.101291.1.1.37
		atg2000c01v1SumHourOffset OBJECT-TYPE
			SYNTAX Int8
			MAX-ACCESS read-write
			STATUS current
			DESCRIPTION
				"It allows selecting the local time offset at summer time"
		::= { atg2000c01v1Entry 37 }

		-- 1.3.6.1.4.1.10106.3.101291.1.1.39
		atg2000c01v1WinMonthSt OBJECT-TYPE
			SYNTAX Month
			MAX-ACCESS read-write
			STATUS current
			DESCRIPTION
				"It allows selecting the month when winter time starts"
		::= { atg2000c01v1Entry 39 }

		-- 1.3.6.1.4.1.10106.3.101291.1.1.41
		atg2000c01v1WinWeekSt OBJECT-TYPE
			SYNTAX WeekOfMonth
			MAX-ACCESS read-write
			STATUS current
			DESCRIPTION
				"It allows selecting the week of the month when winter time starts"
		::= { atg2000c01v1Entry 41 }

		-- 1.3.6.1.4.1.10106.3.101291.1.1.43
		atg2000c01v1WinWDaySt OBJECT-TYPE
			SYNTAX Day
			MAX-ACCESS read-write
			STATUS current
			DESCRIPTION
				"It allows selecting the week day when winter time starts"
		::= { atg2000c01v1Entry 43 }

		-- 1.3.6.1.4.1.10106.3.101291.1.1.45
		atg2000c01v1WinHourSt OBJECT-TYPE
			SYNTAX TimeH1
			MAX-ACCESS read-write
			STATUS current
			DESCRIPTION
				"It allows selecting the UTC hour when winter time starts"
		::= { atg2000c01v1Entry 45 }

		-- 1.3.6.1.4.1.10106.3.101291.1.1.47
		atg2000c01v1WinHourOffset OBJECT-TYPE
			SYNTAX Int8
			MAX-ACCESS read-write
			STATUS current
			DESCRIPTION
				"It allows selecting the local time offset at winter time"
		::= { atg2000c01v1Entry 47 }

		-- 1.3.6.1.4.1.10106.3.101291.1.1.49
		atg2000c01v1EnDlsave OBJECT-TYPE
			SYNTAX BitMask
			MAX-ACCESS read-write
			STATUS current
			DESCRIPTION
				"It allows enabling automatic daylight saving"
		::= { atg2000c01v1Entry 49 }

		-- 1.3.6.1.4.1.10106.3.101291.1.1.51
		atg2000c01v1RefLockFail OBJECT-TYPE
			SYNTAX BitFail
			MAX-ACCESS read-only
			STATUS current
			DESCRIPTION
				"Indicates that the module is not locked to the internal reference"
		::= { atg2000c01v1Entry 51 }

		-- 1.3.6.1.4.1.10106.3.101291.1.1.52
		atg2000c01v1RefLockFailTrapEnable OBJECT-TYPE
			SYNTAX AlarmEnable
			MAX-ACCESS read-write
			STATUS current
			DESCRIPTION
				"Indicates that the module is not locked to the internal reference Trap Enable"
		::= { atg2000c01v1Entry 52 }

		-- 1.3.6.1.4.1.10106.3.101291.1.1.53
		atg2000c01v1TcFail OBJECT-TYPE
			SYNTAX BitFail
			MAX-ACCESS read-only
			STATUS current
			DESCRIPTION
				"Indicates the absence of time and date information in the internal reference"
		::= { atg2000c01v1Entry 53 }

		-- 1.3.6.1.4.1.10106.3.101291.1.1.55
		atg2000c01v1RefPresentFail OBJECT-TYPE
			SYNTAX BitFail
			MAX-ACCESS read-only
			STATUS current
			DESCRIPTION
				"A reference signal was not detected on the internal bus"
		::= { atg2000c01v1Entry 55 }

		-- 1.3.6.1.4.1.10106.3.101291.1.1.57
		atg2000c01v1SerialNo OBJECT-TYPE
			SYNTAX SerialNo
			MAX-ACCESS read-only
			STATUS current
			DESCRIPTION
				"Serial number"
		::= { atg2000c01v1Entry 57 }

		-- 1.3.6.1.4.1.10106.3.540801
		hvd2001c01v1 OBJECT IDENTIFIER ::= { albalaProducts 540801 }

		-- 1.3.6.1.4.1.10106.3.540801.1
		hvd2001c01v1Table  OBJECT-TYPE
			SYNTAX SEQUENCE OF Hvd2001c01v1Entry
			MAX-ACCESS not-accessible
			STATUS current
			DESCRIPTION
				"Module  HVD2001C01V1 Table"
			::= { hvd2001c01v1 1 }

		-- 1.3.6.1.4.1.10106.3.540801.1.1
		hvd2001c01v1Entry  OBJECT-TYPE
			SYNTAX Hvd2001c01v1Entry
			MAX-ACCESS not-accessible
			STATUS current
			DESCRIPTION
				"Module HVD2001C01V1 Entry"
			INDEX { hvd2001c01v1Index }
			::= { hvd2001c01v1Table 1 }

			Hvd2001c01v1Entry ::=
			SEQUENCE {
				hvd2001c01v1Index
				ModuleIndex,
				hvd2001c01v1NoSig
				BitFail,
				hvd2001c01v1NoSigTrapEnable
				AlarmEnable,
				hvd2001c01v1Unlock
				BitFail,
				hvd2001c01v1UnlockTrapEnable
				AlarmEnable,
				hvd2001c01v1Hd
				Bit0Sd1Hd,
				hvd2001c01v1SerialNo
				SerialNo
			 }

		-- 1.3.6.1.4.1.10106.3.101291.1.1.1
		hvd2001c01v1Index OBJECT-TYPE
			SYNTAX ModuleIndex
			MAX-ACCESS read-only
			STATUS current
			DESCRIPTION
				"Index of HVD2001C01V1 Table"
		::= { hvd2001c01v1Entry 1 }

		-- 1.3.6.1.4.1.10106.3.101291.1.1.3
		hvd2001c01v1NoSig OBJECT-TYPE
			SYNTAX BitFail
			MAX-ACCESS read-only
			STATUS current
			DESCRIPTION
				"Input signal status"
		::= { hvd2001c01v1Entry 3 }

		-- 1.3.6.1.4.1.10106.3.101291.1.1.4
		hvd2001c01v1NoSigTrapEnable OBJECT-TYPE
			SYNTAX AlarmEnable
			MAX-ACCESS read-write
			STATUS current
			DESCRIPTION
				"Input signal status Trap Enable"
		::= { hvd2001c01v1Entry 4 }

		-- 1.3.6.1.4.1.10106.3.101291.1.1.5
		hvd2001c01v1Unlock OBJECT-TYPE
			SYNTAX BitFail
			MAX-ACCESS read-only
			STATUS current
			DESCRIPTION
				"Indicates signal unlock fail"
		::= { hvd2001c01v1Entry 5 }

		-- 1.3.6.1.4.1.10106.3.101291.1.1.6
		hvd2001c01v1UnlockTrapEnable OBJECT-TYPE
			SYNTAX AlarmEnable
			MAX-ACCESS read-write
			STATUS current
			DESCRIPTION
				"Indicates signal unlock fail Trap Enable"
		::= { hvd2001c01v1Entry 6 }

		-- 1.3.6.1.4.1.10106.3.101291.1.1.7
		hvd2001c01v1Hd OBJECT-TYPE
			SYNTAX Bit0Sd1Hd
			MAX-ACCESS read-only
			STATUS current
			DESCRIPTION
				"Indicates the SDI signal type"
		::= { hvd2001c01v1Entry 7 }

		-- 1.3.6.1.4.1.10106.3.101291.1.1.9
		hvd2001c01v1SerialNo OBJECT-TYPE
			SYNTAX SerialNo
			MAX-ACCESS read-only
			STATUS current
			DESCRIPTION
				"Serial number"
		::= { hvd2001c01v1Entry 9 }

		-- 1.3.6.1.4.1.10106.3.542501
		gti2000c01v1 OBJECT IDENTIFIER ::= { albalaProducts 542501 }

		-- 1.3.6.1.4.1.10106.3.542501.1
		gti2000c01v1Table  OBJECT-TYPE
			SYNTAX SEQUENCE OF Gti2000c01v1Entry
			MAX-ACCESS not-accessible
			STATUS current
			DESCRIPTION
				"Module  GTI2000C01V1 Table"
			::= { gti2000c01v1 1 }

		-- 1.3.6.1.4.1.10106.3.542501.1.1
		gti2000c01v1Entry  OBJECT-TYPE
			SYNTAX Gti2000c01v1Entry
			MAX-ACCESS not-accessible
			STATUS current
			DESCRIPTION
				"Module GTI2000C01V1 Entry"
			INDEX { gti2000c01v1Index }
			::= { gti2000c01v1Table 1 }

			Gti2000c01v1Entry ::=
			SEQUENCE {
				gti2000c01v1Index
				ModuleIndex,
				gti2000c01v1ActivePreset
				Preset16Active,
				gti2000c01v1LoadPreset
				Preset16Load,
				gti2000c01v1SavePreset
				Preset16Save,
				gti2000c01v1Mode
				ChgOverMode2,
				gti2000c01v1ModeTrapEnable
				AlarmEnable,
				gti2000c01v1InputChgRst
				Bit0No1Yes,
				gti2000c01v1Input
				Ttd2Input,
				gti2000c01v1InputTrapEnable
				AlarmEnable,
				gti2000c01v1InvertPriority
				Bit0No1Yes,
				gti2000c01v1MuteEn
				Bit0No1Yes,
				gti2000c01v1TWait
				TimeS2,
				gti2000c01v1TMute
				TimeS2,
				gti2000c01v1RearFail
				BitFail,
				gti2000c01v1RearFailTrapEnable
				AlarmEnable,
				gti2000c01v1FrontFail
				BitFail,
				gti2000c01v1FrontFailTrapEnable
				AlarmEnable,
				gti2000c01v1Unlock
				BitFail,
				gti2000c01v1UnlockTrapEnable
				AlarmEnable,
				gti2000c01v1SerialNo
				SerialNo
			 }

		-- 1.3.6.1.4.1.10106.3.101291.1.1.1
		gti2000c01v1Index OBJECT-TYPE
			SYNTAX ModuleIndex
			MAX-ACCESS read-only
			STATUS current
			DESCRIPTION
				"Index of GTI2000C01V1 Table"
		::= { gti2000c01v1Entry 1 }

		-- 1.3.6.1.4.1.10106.3.101291.1.1.3
		gti2000c01v1ActivePreset OBJECT-TYPE
			SYNTAX Preset16Active
			MAX-ACCESS read-only
			STATUS current
			DESCRIPTION
				"Shows the active preset"
		::= { gti2000c01v1Entry 3 }

		-- 1.3.6.1.4.1.10106.3.101291.1.1.5
		gti2000c01v1LoadPreset OBJECT-TYPE
			SYNTAX Preset16Load
			MAX-ACCESS read-write
			STATUS current
			DESCRIPTION
				"Allows loading a preset"
		::= { gti2000c01v1Entry 5 }

		-- 1.3.6.1.4.1.10106.3.101291.1.1.7
		gti2000c01v1SavePreset OBJECT-TYPE
			SYNTAX Preset16Save
			MAX-ACCESS read-write
			STATUS current
			DESCRIPTION
				"Allows saving a preset"
		::= { gti2000c01v1Entry 7 }

		-- 1.3.6.1.4.1.10106.3.101291.1.1.9
		gti2000c01v1Mode OBJECT-TYPE
			SYNTAX ChgOverMode2
			MAX-ACCESS read-write
			STATUS current
			DESCRIPTION
				"Allows selecting the switching mode"
		::= { gti2000c01v1Entry 9 }

		-- 1.3.6.1.4.1.10106.3.101291.1.1.10
		gti2000c01v1ModeTrapEnable OBJECT-TYPE
			SYNTAX AlarmEnable
			MAX-ACCESS read-write
			STATUS current
			DESCRIPTION
				"Allows selecting the switching mode Trap Enable"
		::= { gti2000c01v1Entry 10 }

		-- 1.3.6.1.4.1.10106.3.101291.1.1.11
		gti2000c01v1InputChgRst OBJECT-TYPE
			SYNTAX Bit0No1Yes
			MAX-ACCESS read-write
			STATUS current
			DESCRIPTION
				"Indicates a change in which input is used as reference"
		::= { gti2000c01v1Entry 11 }

		-- 1.3.6.1.4.1.10106.3.101291.1.1.13
		gti2000c01v1Input OBJECT-TYPE
			SYNTAX Ttd2Input
			MAX-ACCESS read-write
			STATUS current
			DESCRIPTION
				"Allows selecting the reference input"
		::= { gti2000c01v1Entry 13 }

		-- 1.3.6.1.4.1.10106.3.101291.1.1.14
		gti2000c01v1InputTrapEnable OBJECT-TYPE
			SYNTAX AlarmEnable
			MAX-ACCESS read-write
			STATUS current
			DESCRIPTION
				"Allows selecting the reference input Trap Enable"
		::= { gti2000c01v1Entry 14 }

		-- 1.3.6.1.4.1.10106.3.101291.1.1.15
		gti2000c01v1InvertPriority OBJECT-TYPE
			SYNTAX Bit0No1Yes
			MAX-ACCESS read-write
			STATUS current
			DESCRIPTION
				"Allows changing the input priority"
		::= { gti2000c01v1Entry 15 }

		-- 1.3.6.1.4.1.10106.3.101291.1.1.17
		gti2000c01v1MuteEn OBJECT-TYPE
			SYNTAX Bit0No1Yes
			MAX-ACCESS read-write
			STATUS current
			DESCRIPTION
				"Mutes outputs when selected input is not present"
		::= { gti2000c01v1Entry 17 }

		-- 1.3.6.1.4.1.10106.3.101291.1.1.19
		gti2000c01v1TWait OBJECT-TYPE
			SYNTAX TimeS2
			MAX-ACCESS read-write
			STATUS current
			DESCRIPTION
				"Amount of time that an input must be stable before it is considered valid and used as reference"
		::= { gti2000c01v1Entry 19 }

		-- 1.3.6.1.4.1.10106.3.101291.1.1.21
		gti2000c01v1TMute OBJECT-TYPE
			SYNTAX TimeS2
			MAX-ACCESS read-write
			STATUS current
			DESCRIPTION
				"Amount of time with no valid reference before output is disabled"
		::= { gti2000c01v1Entry 21 }

		-- 1.3.6.1.4.1.10106.3.101291.1.1.23
		gti2000c01v1RearFail OBJECT-TYPE
			SYNTAX BitFail
			MAX-ACCESS read-only
			STATUS current
			DESCRIPTION
				"Indicates lack of valid rear reference"
		::= { gti2000c01v1Entry 23 }

		-- 1.3.6.1.4.1.10106.3.101291.1.1.24
		gti2000c01v1RearFailTrapEnable OBJECT-TYPE
			SYNTAX AlarmEnable
			MAX-ACCESS read-write
			STATUS current
			DESCRIPTION
				"Indicates lack of valid rear reference Trap Enable"
		::= { gti2000c01v1Entry 24 }

		-- 1.3.6.1.4.1.10106.3.101291.1.1.25
		gti2000c01v1FrontFail OBJECT-TYPE
			SYNTAX BitFail
			MAX-ACCESS read-only
			STATUS current
			DESCRIPTION
				"Indicates lack of valid front reference"
		::= { gti2000c01v1Entry 25 }

		-- 1.3.6.1.4.1.10106.3.101291.1.1.26
		gti2000c01v1FrontFailTrapEnable OBJECT-TYPE
			SYNTAX AlarmEnable
			MAX-ACCESS read-write
			STATUS current
			DESCRIPTION
				"Indicates lack of valid front reference Trap Enable"
		::= { gti2000c01v1Entry 26 }

		-- 1.3.6.1.4.1.10106.3.101291.1.1.27
		gti2000c01v1Unlock OBJECT-TYPE
			SYNTAX BitFail
			MAX-ACCESS read-only
			STATUS current
			DESCRIPTION
				"Reference lock fail"
		::= { gti2000c01v1Entry 27 }

		-- 1.3.6.1.4.1.10106.3.101291.1.1.28
		gti2000c01v1UnlockTrapEnable OBJECT-TYPE
			SYNTAX AlarmEnable
			MAX-ACCESS read-write
			STATUS current
			DESCRIPTION
				"Reference lock fail Trap Enable"
		::= { gti2000c01v1Entry 28 }

		-- 1.3.6.1.4.1.10106.3.101291.1.1.29
		gti2000c01v1SerialNo OBJECT-TYPE
			SYNTAX SerialNo
			MAX-ACCESS read-only
			STATUS current
			DESCRIPTION
				"Serial number"
		::= { gti2000c01v1Entry 29 }

		-- 1.3.6.1.4.1.10106.3.550001
		ste2022c01v1 OBJECT IDENTIFIER ::= { albalaProducts 550001 }

		-- 1.3.6.1.4.1.10106.3.550001.1
		ste2022c01v1Table  OBJECT-TYPE
			SYNTAX SEQUENCE OF Ste2022c01v1Entry
			MAX-ACCESS not-accessible
			STATUS current
			DESCRIPTION
				"Module  STE2022C01V1 Table"
			::= { ste2022c01v1 1 }

		-- 1.3.6.1.4.1.10106.3.550001.1.1
		ste2022c01v1Entry  OBJECT-TYPE
			SYNTAX Ste2022c01v1Entry
			MAX-ACCESS not-accessible
			STATUS current
			DESCRIPTION
				"Module STE2022C01V1 Entry"
			INDEX { ste2022c01v1Index }
			::= { ste2022c01v1Table 1 }

			Ste2022c01v1Entry ::=
			SEQUENCE {
				ste2022c01v1Index
				ModuleIndex,
				ste2022c01v1ActivePreset
				Preset16Active,
				ste2022c01v1LoadPreset
				Preset16Load,
				ste2022c01v1SavePreset
				Preset16Save,
				ste2022c01v1StatReset
				Bit0No1Yes,
				ste2022c01v1StatMode
				Bit01s1Total,
				ste2022c01v1InpFailMode
				Bit0No1Yes,
				ste2022c01v1DirControl1
				SteDirControl,
				ste2022c01v1DirControl2
				SteDirControl,
				ste2022c01v1DirControl3
				SteDirControl,
				ste2022c01v1DirControl4
				SteDirControl,
				ste2022c01v1FrBufferMod1
				Bit0Lin1Fra,
				ste2022c01v1FrBufferMod2
				Bit0Lin1Fra,
				ste2022c01v1FrBufferMod3
				Bit0Lin1Fra,
				ste2022c01v1FrBufferMod4
				Bit0Lin1Fra,
				ste2022c01v1RefInput
				RefSel2,
				ste2022c01v1ExpRefFormat
				Bit06251525,
				ste2022c01v1RefLckFailMsk
				BitMask,
				ste2022c01v1TimeOut
				TimeS4,
				ste2022c01v1Tx1UniEna
				Bit0No1Yes,
				ste2022c01v1Tx1MultiEna
				IpaTxMode,
				ste2022c01v1Tx1FecMode
				FecModeSte,
				ste2022c01v1TimestampCf1
				Bit0No1Yes,
				ste2022c01v1Tx1UipAdd3
				Uint8,
				ste2022c01v1Tx1UipAdd2
				Uint8,
				ste2022c01v1Tx1UipAdd1
				Uint8,
				ste2022c01v1Tx1UipAdd0
				Uint8,
				ste2022c01v1Tx1MipAdd3
				Uint8,
				ste2022c01v1Tx1MipAdd2
				Uint8,
				ste2022c01v1Tx1MipAdd1
				Uint8,
				ste2022c01v1Tx1MipAdd0
				Uint8,
				ste2022c01v1Tx1SPort
				Uint16,
				ste2022c01v1Tx1DPort
				Uint16,
				ste2022c01v1Tx1LParam
				Uint8,
				ste2022c01v1Tx1DParam
				Uint8,
				ste2022c01v1Tx1RowDelay
				Uint16,
				ste2022c01v1Tx1ColDelay
				Uint16,
				ste2022c01v1TxIp1SrAdd3
				Uint8,
				ste2022c01v1TxIp1SrAdd2
				Uint8,
				ste2022c01v1TxIp1SrAdd1
				Uint8,
				ste2022c01v1TxIp1SrAdd0
				Uint8,
				ste2022c01v1TxIp1SrMsk0
				Uint8,
				ste2022c01v1TxIp1SrMsk1
				Uint8,
				ste2022c01v1TxIp1SrMsk2
				Uint8,
				ste2022c01v1TxIp1SrMsk3
				Uint8,
				ste2022c01v1Tx2UniEna
				Bit0No1Yes,
				ste2022c01v1Tx2MultiEna
				IpaTxMode,
				ste2022c01v1Tx2FecMode
				FecModeSte,
				ste2022c01v1TimestampCf2
				Bit0No1Yes,
				ste2022c01v1Tx2UipAdd3
				Uint8,
				ste2022c01v1Tx2UipAdd2
				Uint8,
				ste2022c01v1Tx2UipAdd1
				Uint8,
				ste2022c01v1Tx2UipAdd0
				Uint8,
				ste2022c01v1Tx2MipAdd3
				Uint8,
				ste2022c01v1Tx2MipAdd2
				Uint8,
				ste2022c01v1Tx2MipAdd1
				Uint8,
				ste2022c01v1Tx2MipAdd0
				Uint8,
				ste2022c01v1Tx2SPort
				Uint16,
				ste2022c01v1Tx2DPort
				Uint16,
				ste2022c01v1Tx2LParam
				Uint8,
				ste2022c01v1Tx2DParam
				Uint8,
				ste2022c01v1Tx2RowDelay
				Uint16,
				ste2022c01v1Tx2ColDelay
				Uint16,
				ste2022c01v1TxIp2SrAdd3
				Uint8,
				ste2022c01v1TxIp2SrAdd2
				Uint8,
				ste2022c01v1TxIp2SrAdd1
				Uint8,
				ste2022c01v1TxIp2SrAdd0
				Uint8,
				ste2022c01v1TxIp2SrMsk0
				Uint8,
				ste2022c01v1TxIp2SrMsk1
				Uint8,
				ste2022c01v1TxIp2SrMsk2
				Uint8,
				ste2022c01v1TxIp2SrMsk3
				Uint8,
				ste2022c01v1Tx3UniEna
				Bit0No1Yes,
				ste2022c01v1Tx3MultiEna
				IpaTxMode,
				ste2022c01v1Tx3FecMode
				FecModeSte,
				ste2022c01v1TimestampCf3
				Bit0No1Yes,
				ste2022c01v1Tx3UipAdd3
				Uint8,
				ste2022c01v1Tx3UipAdd2
				Uint8,
				ste2022c01v1Tx3UipAdd1
				Uint8,
				ste2022c01v1Tx3UipAdd0
				Uint8,
				ste2022c01v1Tx3MipAdd3
				Uint8,
				ste2022c01v1Tx3MipAdd2
				Uint8,
				ste2022c01v1Tx3MipAdd1
				Uint8,
				ste2022c01v1Tx3MipAdd0
				Uint8,
				ste2022c01v1Tx3SPort
				Uint16,
				ste2022c01v1Tx3DPort
				Uint16,
				ste2022c01v1Tx3LParam
				Uint8,
				ste2022c01v1Tx3DParam
				Uint8,
				ste2022c01v1Tx3RowDelay
				Uint16,
				ste2022c01v1Tx3ColDelay
				Uint16,
				ste2022c01v1TxIp3SrAdd3
				Uint8,
				ste2022c01v1TxIp3SrAdd2
				Uint8,
				ste2022c01v1TxIp3SrAdd1
				Uint8,
				ste2022c01v1TxIp3SrAdd0
				Uint8,
				ste2022c01v1TxIp3SrMsk3
				Uint8,
				ste2022c01v1TxIp3SrMsk2
				Uint8,
				ste2022c01v1TxIp3SrMsk1
				Uint8,
				ste2022c01v1TxIp3SrMsk0
				Uint8,
				ste2022c01v1Tx4UniEna
				Bit0No1Yes,
				ste2022c01v1Tx4MultiEna
				IpaTxMode,
				ste2022c01v1Tx4FecMode
				FecModeSte,
				ste2022c01v1TimestampCf4
				Bit0No1Yes,
				ste2022c01v1Tx4UipAdd3
				Uint8,
				ste2022c01v1Tx4UipAdd2
				Uint8,
				ste2022c01v1Tx4UipAdd1
				Uint8,
				ste2022c01v1Tx4UipAdd0
				Uint8,
				ste2022c01v1Tx4MipAdd3
				Uint8,
				ste2022c01v1Tx4MipAdd2
				Uint8,
				ste2022c01v1Tx4MipAdd1
				Uint8,
				ste2022c01v1Tx4MipAdd0
				Uint8,
				ste2022c01v1Tx4SPort
				Uint16,
				ste2022c01v1Tx4DPort
				Uint16,
				ste2022c01v1Tx4LParam
				Uint8,
				ste2022c01v1Tx4DParam
				Uint8,
				ste2022c01v1Tx4RowDelay
				Uint16,
				ste2022c01v1Tx4ColDelay
				Uint16,
				ste2022c01v1TxIp4SrAdd3
				Uint8,
				ste2022c01v1TxIp4SrAdd2
				Uint8,
				ste2022c01v1TxIp4SrAdd1
				Uint8,
				ste2022c01v1TxIp4SrAdd0
				Uint8,
				ste2022c01v1TxIp4SrMsk3
				Uint8,
				ste2022c01v1TxIp4SrMsk2
				Uint8,
				ste2022c01v1TxIp4SrMsk1
				Uint8,
				ste2022c01v1TxIp4SrMsk0
				Uint8,
				ste2022c01v1Str1Ena
				Bit0No1Yes,
				ste2022c01v1Str1MulticEna
				IpaTxMode,
				ste2022c01v1Str1FecEna
				Bit0No1Yes,
				ste2022c01v1Str1UipDAdd3
				Uint8,
				ste2022c01v1Str1UipDAdd2
				Uint8,
				ste2022c01v1Str1UipDAdd1
				Uint8,
				ste2022c01v1Str1UipDAdd0
				Uint8,
				ste2022c01v1Str1MipDAdd3
				Uint8,
				ste2022c01v1Str1MipDAdd2
				Uint8,
				ste2022c01v1Str1MipDAdd1
				Uint8,
				ste2022c01v1Str1MipDAdd0
				Uint8,
				ste2022c01v1Str1IgmFAdd3
				Uint8,
				ste2022c01v1Str1IgmFAdd2
				Uint8,
				ste2022c01v1Str1IgmFAdd1
				Uint8,
				ste2022c01v1Str1IgmFAdd0
				Uint8,
				ste2022c01v1Str1DPort
				Uint16,
				ste2022c01v1RxIp1SrMsk
				Uint8,
				ste2022c01v1RxIp1SrMsk2
				Uint8,
				ste2022c01v1RxIp1SrMsk1
				Uint8,
				ste2022c01v1RxIp1SrMsk0
				Uint8,
				ste2022c01v1Str2Ena
				Bit0No1Yes,
				ste2022c01v1Str2MulticEna
				IpaTxMode,
				ste2022c01v1Str2FecEna
				Bit0No1Yes,
				ste2022c01v1Str2UipDAdd3
				Uint8,
				ste2022c01v1Str2UipDAdd2
				Uint8,
				ste2022c01v1Str2UipDAdd1
				Uint8,
				ste2022c01v1Str2UipDAdd0
				Uint8,
				ste2022c01v1Str2MipDAdd3
				Uint8,
				ste2022c01v1Str2MipDAdd2
				Uint8,
				ste2022c01v1Str2MipDAdd1
				Uint8,
				ste2022c01v1Str2MipDAdd0
				Uint8,
				ste2022c01v1Str2IgmFAdd3
				Uint8,
				ste2022c01v1Str2IgmFAdd2
				Uint8,
				ste2022c01v1Str2IgmFAdd1
				Uint8,
				ste2022c01v1Str2IgmFAdd0
				Uint8,
				ste2022c01v1Str2DPort
				Uint16,
				ste2022c01v1RxIp2SrMsk
				Uint8,
				ste2022c01v1RxIp2SrMsk1
				Uint8,
				ste2022c01v1RxIp2SrMsk2
				Uint8,
				ste2022c01v1RxIp2SrMsk3
				Uint8,
				ste2022c01v1Str3Ena
				Bit0No1Yes,
				ste2022c01v1Str3MulticEna
				IpaTxMode,
				ste2022c01v1Str3FecEna
				Bit0No1Yes,
				ste2022c01v1Str3UipDAdd3
				Uint8,
				ste2022c01v1Str3UipDAdd2
				Uint8,
				ste2022c01v1Str3UipDAdd1
				Uint8,
				ste2022c01v1Str3UipDAdd0
				Uint8,
				ste2022c01v1Str3MipDAdd3
				Uint8,
				ste2022c01v1Str3MipDAdd2
				Uint8,
				ste2022c01v1Str3MipDAdd1
				Uint8,
				ste2022c01v1Str3MipDAdd0
				Uint8,
				ste2022c01v1Str3IgmFAdd3
				Uint8,
				ste2022c01v1Str3IgmFAdd2
				Uint8,
				ste2022c01v1Str3IgmFAdd1
				Uint8,
				ste2022c01v1Str3IgmFAdd0
				Uint8,
				ste2022c01v1Str3DPort
				Uint16,
				ste2022c01v1RxIp3SrMsk3
				Uint8,
				ste2022c01v1RxIp3SrMsk2
				Uint8,
				ste2022c01v1RxIp3SrMsk1
				Uint8,
				ste2022c01v1RxIp3SrMsk0
				Uint8,
				ste2022c01v1Str4Ena
				Bit0No1Yes,
				ste2022c01v1Str4MulticEna
				IpaTxMode,
				ste2022c01v1Str4FecEna
				Bit0No1Yes,
				ste2022c01v1Str4UipDAdd3
				Uint8,
				ste2022c01v1Str4UipDAdd2
				Uint8,
				ste2022c01v1Str4UipDAdd1
				Uint8,
				ste2022c01v1Str4UipDAdd0
				Uint8,
				ste2022c01v1Str4MipDAdd3
				Uint8,
				ste2022c01v1Str4MipDAdd2
				Uint8,
				ste2022c01v1Str4MipDAdd1
				Uint8,
				ste2022c01v1Str4MipDAdd0
				Uint8,
				ste2022c01v1Str4IgmFAdd3
				Uint8,
				ste2022c01v1Str4IgmFAdd2
				Uint8,
				ste2022c01v1Str4IgmFAdd1
				Uint8,
				ste2022c01v1Str4IgmFAdd0
				Uint8,
				ste2022c01v1Str4DPort
				Uint16,
				ste2022c01v1RxIp4SrMsk3
				Uint8,
				ste2022c01v1RxIp4SrMsk2
				Uint8,
				ste2022c01v1RxIp4SrMsk1
				Uint8,
				ste2022c01v1RxIp4SrMsk0
				Uint8,
				ste2022c01v1Rx1FecMode
				FecModeSte,
				ste2022c01v1Rx1IpRxAdd3
				Uint8,
				ste2022c01v1Rx1IpRxAdd2
				Uint8,
				ste2022c01v1Rx1IpRxAdd1
				Uint8,
				ste2022c01v1Rx1IpRxAdd0
				Uint8,
				ste2022c01v1Rx1IpRxPort
				Uint16,
				ste2022c01v1Rx1LParam
				Uint16,
				ste2022c01v1Rx1DParam
				Uint16,
				ste2022c01v1Rx2FecMode
				FecModeSte,
				ste2022c01v1Rx2IpRxAdd3
				Uint8,
				ste2022c01v1Rx2IpRxAdd2
				Uint8,
				ste2022c01v1Rx2IpRxAdd1
				Uint8,
				ste2022c01v1Rx2IpRxAdd0
				Uint8,
				ste2022c01v1Rx2IpRxPort
				Uint16,
				ste2022c01v1Rx2LParam
				Uint16,
				ste2022c01v1Rx2DParam
				Uint16,
				ste2022c01v1Rx3FecMode
				FecModeSte,
				ste2022c01v1Rx3IpRxAdd3
				Uint8,
				ste2022c01v1Rx3IpRxAdd2
				Uint8,
				ste2022c01v1Rx3IpRxAdd1
				Uint8,
				ste2022c01v1Rx3IpRxAdd0
				Uint8,
				ste2022c01v1Rx3IpRxPort
				Uint16,
				ste2022c01v1Rx3LParam
				Uint16,
				ste2022c01v1Rx3DParam
				Uint16,
				ste2022c01v1Rx4FecMode
				FecModeSte,
				ste2022c01v1Rx4IpRxAdd3
				Uint8,
				ste2022c01v1Rx4IpRxAdd2
				Uint8,
				ste2022c01v1Rx4IpRxAdd1
				Uint8,
				ste2022c01v1Rx4IpRxAdd0
				Uint8,
				ste2022c01v1Rx4IpRxPort
				Uint16,
				ste2022c01v1Rx4LParam
				Uint16,
				ste2022c01v1Rx4DParam
				Uint16,
				ste2022c01v1LocalIp2Add3
				Uint8,
				ste2022c01v1LocalIp2Add2
				Uint8,
				ste2022c01v1LocalIp2Add1
				Uint8,
				ste2022c01v1LocalIp2Add0
				Uint8,
				ste2022c01v1LocalIp2Msk3
				Uint8,
				ste2022c01v1LocalIp2Msk2
				Uint8,
				ste2022c01v1LocalIp2Msk1
				Uint8,
				ste2022c01v1LocalIp2Msk0
				Uint8,
				ste2022c01v1LocalIpGway3
				Uint8,
				ste2022c01v1LocalIpGway2
				Uint8,
				ste2022c01v1LocalIpGway1
				Uint8,
				ste2022c01v1LocalIpGway0
				Uint8,
				ste2022c01v1SysError
				SysError0,
				ste2022c01v1NoSignal1
				BitFail,
				ste2022c01v1NoSignal1Aux
				BitFail,
				ste2022c01v1EdhCrc1
				BitFail,
				ste2022c01v1Format1
				SdiHd3gFmt3,
				ste2022c01v1Format1Aux
				SdiHd3gFmt3,
				ste2022c01v1NoSignal2
				BitFail,
				ste2022c01v1EdhCrc2
				BitFail,
				ste2022c01v1Format2
				SdiHd3gFmt3,
				ste2022c01v1NoSignal3
				BitFail,
				ste2022c01v1EdhCrc3
				BitFail,
				ste2022c01v1Format3
				SdiHd3gFmt3,
				ste2022c01v1NoSignal4
				BitFail,
				ste2022c01v1EdhCrc4
				BitFail,
				ste2022c01v1Format4
				SdiHd3gFmt3,
				ste2022c01v1FormatIp1
				SdiHd3gFmt3,
				ste2022c01v1RxIpFail1
				BitFail,
				ste2022c01v1LostLine1
				BitFail,
				ste2022c01v1FormatIp2
				SdiHd3gFmt3,
				ste2022c01v1RxIpFail2
				BitFail,
				ste2022c01v1LostLine2
				BitFail,
				ste2022c01v1FormatIp3
				SdiHd3gFmt3,
				ste2022c01v1RxIpFail3
				BitFail,
				ste2022c01v1LostLine3
				BitFail,
				ste2022c01v1FormatIp4
				SdiHd3gFmt3,
				ste2022c01v1RxIpFail4
				BitFail,
				ste2022c01v1LostLine4
				BitFail,
				ste2022c01v1Link
				EthStatus,
				ste2022c01v1EthRemoteFault
				BitFail,
				ste2022c01v1EthTxActivity
				BitEthActivity,
				ste2022c01v1EthRxActivity
				BitEthActivity,
				ste2022c01v1ArpValid1
				BitFailN,
				ste2022c01v1IcmpError1
				BitFail,
				ste2022c01v1ArpValid2
				BitFailN,
				ste2022c01v1IcmpError2
				BitFail,
				ste2022c01v1ArpValid3
				BitFailN,
				ste2022c01v1IcmpError3
				BitFail,
				ste2022c01v1ArpValid4
				BitFailN,
				ste2022c01v1IcmpError4
				BitFail,
				ste2022c01v1RefLockFail
				BitFailN,
				ste2022c01v1IntRefPres
				BitFail,
				ste2022c01v1GlobalStatus
				BitFailN,
				ste2022c01v1SpeedStatus
				BitFail,
				ste2022c01v1Temperature
				TempKintex,
				ste2022c01v1SerialNo
				SerialNo
			 }

		-- 1.3.6.1.4.1.10106.3.101291.1.1.1
		ste2022c01v1Index OBJECT-TYPE
			SYNTAX ModuleIndex
			MAX-ACCESS read-only
			STATUS current
			DESCRIPTION
				"Index of STE2022C01V1 Table"
		::= { ste2022c01v1Entry 1 }

		-- 1.3.6.1.4.1.10106.3.101291.1.1.3
		ste2022c01v1ActivePreset OBJECT-TYPE
			SYNTAX Preset16Active
			MAX-ACCESS read-only
			STATUS current
			DESCRIPTION
				"Shows the active preset"
		::= { ste2022c01v1Entry 3 }

		-- 1.3.6.1.4.1.10106.3.101291.1.1.5
		ste2022c01v1LoadPreset OBJECT-TYPE
			SYNTAX Preset16Load
			MAX-ACCESS read-write
			STATUS current
			DESCRIPTION
				"Allows loading a preset"
		::= { ste2022c01v1Entry 5 }

		-- 1.3.6.1.4.1.10106.3.101291.1.1.7
		ste2022c01v1SavePreset OBJECT-TYPE
			SYNTAX Preset16Save
			MAX-ACCESS read-write
			STATUS current
			DESCRIPTION
				"Allows saving a preset"
		::= { ste2022c01v1Entry 7 }

		-- 1.3.6.1.4.1.10106.3.101291.1.1.9
		ste2022c01v1StatReset OBJECT-TYPE
			SYNTAX Bit0No1Yes
			MAX-ACCESS read-write
			STATUS current
			DESCRIPTION
				"Allows reseting the statistics measurements"
		::= { ste2022c01v1Entry 9 }

		-- 1.3.6.1.4.1.10106.3.101291.1.1.11
		ste2022c01v1StatMode OBJECT-TYPE
			SYNTAX Bit01s1Total
			MAX-ACCESS read-write
			STATUS current
			DESCRIPTION
				"Allows selecting the statistics mode"
		::= { ste2022c01v1Entry 11 }

		-- 1.3.6.1.4.1.10106.3.101291.1.1.13
		ste2022c01v1InpFailMode OBJECT-TYPE
			SYNTAX Bit0No1Yes
			MAX-ACCESS read-write
			STATUS current
			DESCRIPTION
				"Selects if the output is muted when the input fail"
		::= { ste2022c01v1Entry 13 }

		-- 1.3.6.1.4.1.10106.3.101291.1.1.15
		ste2022c01v1DirControl1 OBJECT-TYPE
			SYNTAX SteDirControl
			MAX-ACCESS read-write
			STATUS current
			DESCRIPTION
				"Selects the processor working mode"
		::= { ste2022c01v1Entry 15 }

		-- 1.3.6.1.4.1.10106.3.101291.1.1.17
		ste2022c01v1DirControl2 OBJECT-TYPE
			SYNTAX SteDirControl
			MAX-ACCESS read-write
			STATUS current
			DESCRIPTION
				"Selects the processo working mode"
		::= { ste2022c01v1Entry 17 }

		-- 1.3.6.1.4.1.10106.3.101291.1.1.19
		ste2022c01v1DirControl3 OBJECT-TYPE
			SYNTAX SteDirControl
			MAX-ACCESS read-write
			STATUS current
			DESCRIPTION
				"Selects the processo working mode"
		::= { ste2022c01v1Entry 19 }

		-- 1.3.6.1.4.1.10106.3.101291.1.1.21
		ste2022c01v1DirControl4 OBJECT-TYPE
			SYNTAX SteDirControl
			MAX-ACCESS read-write
			STATUS current
			DESCRIPTION
				"Selects the processo working mode"
		::= { ste2022c01v1Entry 21 }

		-- 1.3.6.1.4.1.10106.3.101291.1.1.23
		ste2022c01v1FrBufferMod1 OBJECT-TYPE
			SYNTAX Bit0Lin1Fra
			MAX-ACCESS read-write
			STATUS current
			DESCRIPTION
				"Allows selecting the synchronizing mode"
		::= { ste2022c01v1Entry 23 }

		-- 1.3.6.1.4.1.10106.3.101291.1.1.25
		ste2022c01v1FrBufferMod2 OBJECT-TYPE
			SYNTAX Bit0Lin1Fra
			MAX-ACCESS read-write
			STATUS current
			DESCRIPTION
				"Allows selecting the synchronizing mode"
		::= { ste2022c01v1Entry 25 }

		-- 1.3.6.1.4.1.10106.3.101291.1.1.27
		ste2022c01v1FrBufferMod3 OBJECT-TYPE
			SYNTAX Bit0Lin1Fra
			MAX-ACCESS read-write
			STATUS current
			DESCRIPTION
				"Allows selecting the synchronizing mode"
		::= { ste2022c01v1Entry 27 }

		-- 1.3.6.1.4.1.10106.3.101291.1.1.29
		ste2022c01v1FrBufferMod4 OBJECT-TYPE
			SYNTAX Bit0Lin1Fra
			MAX-ACCESS read-write
			STATUS current
			DESCRIPTION
				"Allows selecting the synchronizing mode"
		::= { ste2022c01v1Entry 29 }

		-- 1.3.6.1.4.1.10106.3.101291.1.1.31
		ste2022c01v1RefInput OBJECT-TYPE
			SYNTAX RefSel2
			MAX-ACCESS read-write
			STATUS current
			DESCRIPTION
				"Allows selecting the reference input"
		::= { ste2022c01v1Entry 31 }

		-- 1.3.6.1.4.1.10106.3.101291.1.1.33
		ste2022c01v1ExpRefFormat OBJECT-TYPE
			SYNTAX Bit06251525
			MAX-ACCESS read-write
			STATUS current
			DESCRIPTION
				"Allows selecting the expected format of the reference"
		::= { ste2022c01v1Entry 33 }

		-- 1.3.6.1.4.1.10106.3.101291.1.1.35
		ste2022c01v1RefLckFailMsk OBJECT-TYPE
			SYNTAX BitMask
			MAX-ACCESS read-write
			STATUS current
			DESCRIPTION
				"Allows masking the reference lock fail"
		::= { ste2022c01v1Entry 35 }

		-- 1.3.6.1.4.1.10106.3.101291.1.1.37
		ste2022c01v1TimeOut OBJECT-TYPE
			SYNTAX TimeS4
			MAX-ACCESS read-write
			STATUS current
			DESCRIPTION
				"Time out before silence/black"
		::= { ste2022c01v1Entry 37 }

		-- 1.3.6.1.4.1.10106.3.101291.1.1.39
		ste2022c01v1Tx1UniEna OBJECT-TYPE
			SYNTAX Bit0No1Yes
			MAX-ACCESS read-write
			STATUS current
			DESCRIPTION
				"Enable TX"
		::= { ste2022c01v1Entry 39 }

		-- 1.3.6.1.4.1.10106.3.101291.1.1.41
		ste2022c01v1Tx1MultiEna OBJECT-TYPE
			SYNTAX IpaTxMode
			MAX-ACCESS read-write
			STATUS current
			DESCRIPTION
				"TX mode"
		::= { ste2022c01v1Entry 41 }

		-- 1.3.6.1.4.1.10106.3.101291.1.1.43
		ste2022c01v1Tx1FecMode OBJECT-TYPE
			SYNTAX FecModeSte
			MAX-ACCESS read-write
			STATUS current
			DESCRIPTION
				"Protocol"
		::= { ste2022c01v1Entry 43 }

		-- 1.3.6.1.4.1.10106.3.101291.1.1.45
		ste2022c01v1TimestampCf1 OBJECT-TYPE
			SYNTAX Bit0No1Yes
			MAX-ACCESS read-write
			STATUS current
			DESCRIPTION
				"Timestamp insertion (SMPTE2022 header)"
		::= { ste2022c01v1Entry 45 }

		-- 1.3.6.1.4.1.10106.3.101291.1.1.47
		ste2022c01v1Tx1UipAdd3 OBJECT-TYPE
			SYNTAX Uint8
			MAX-ACCESS read-write
			STATUS current
			DESCRIPTION
				"Destination IP address (3)"
		::= { ste2022c01v1Entry 47 }

		-- 1.3.6.1.4.1.10106.3.101291.1.1.49
		ste2022c01v1Tx1UipAdd2 OBJECT-TYPE
			SYNTAX Uint8
			MAX-ACCESS read-write
			STATUS current
			DESCRIPTION
				"Destination IP address (2)"
		::= { ste2022c01v1Entry 49 }

		-- 1.3.6.1.4.1.10106.3.101291.1.1.51
		ste2022c01v1Tx1UipAdd1 OBJECT-TYPE
			SYNTAX Uint8
			MAX-ACCESS read-write
			STATUS current
			DESCRIPTION
				"Destination IP address (1)"
		::= { ste2022c01v1Entry 51 }

		-- 1.3.6.1.4.1.10106.3.101291.1.1.53
		ste2022c01v1Tx1UipAdd0 OBJECT-TYPE
			SYNTAX Uint8
			MAX-ACCESS read-write
			STATUS current
			DESCRIPTION
				"Destination IP address (0)"
		::= { ste2022c01v1Entry 53 }

		-- 1.3.6.1.4.1.10106.3.101291.1.1.55
		ste2022c01v1Tx1MipAdd3 OBJECT-TYPE
			SYNTAX Uint8
			MAX-ACCESS read-write
			STATUS current
			DESCRIPTION
				"Multicast dest. IP address (3)"
		::= { ste2022c01v1Entry 55 }

		-- 1.3.6.1.4.1.10106.3.101291.1.1.57
		ste2022c01v1Tx1MipAdd2 OBJECT-TYPE
			SYNTAX Uint8
			MAX-ACCESS read-write
			STATUS current
			DESCRIPTION
				"Multicast dest. IP address (2)"
		::= { ste2022c01v1Entry 57 }

		-- 1.3.6.1.4.1.10106.3.101291.1.1.59
		ste2022c01v1Tx1MipAdd1 OBJECT-TYPE
			SYNTAX Uint8
			MAX-ACCESS read-write
			STATUS current
			DESCRIPTION
				"Multicast dest. IP address (1)"
		::= { ste2022c01v1Entry 59 }

		-- 1.3.6.1.4.1.10106.3.101291.1.1.61
		ste2022c01v1Tx1MipAdd0 OBJECT-TYPE
			SYNTAX Uint8
			MAX-ACCESS read-write
			STATUS current
			DESCRIPTION
				"Multicast dest. IP address (0)"
		::= { ste2022c01v1Entry 61 }

		-- 1.3.6.1.4.1.10106.3.101291.1.1.63
		ste2022c01v1Tx1SPort OBJECT-TYPE
			SYNTAX Uint16
			MAX-ACCESS read-write
			STATUS current
			DESCRIPTION
				"Source port"
		::= { ste2022c01v1Entry 63 }

		-- 1.3.6.1.4.1.10106.3.101291.1.1.65
		ste2022c01v1Tx1DPort OBJECT-TYPE
			SYNTAX Uint16
			MAX-ACCESS read-write
			STATUS current
			DESCRIPTION
				"Destination port"
		::= { ste2022c01v1Entry 65 }

		-- 1.3.6.1.4.1.10106.3.101291.1.1.67
		ste2022c01v1Tx1LParam OBJECT-TYPE
			SYNTAX Uint8
			MAX-ACCESS read-write
			STATUS current
			DESCRIPTION
				"L parameter (FEC mode columns)"
		::= { ste2022c01v1Entry 67 }

		-- 1.3.6.1.4.1.10106.3.101291.1.1.69
		ste2022c01v1Tx1DParam OBJECT-TYPE
			SYNTAX Uint8
			MAX-ACCESS read-write
			STATUS current
			DESCRIPTION
				"D parameter (FEC mode rows)"
		::= { ste2022c01v1Entry 69 }

		-- 1.3.6.1.4.1.10106.3.101291.1.1.71
		ste2022c01v1Tx1RowDelay OBJECT-TYPE
			SYNTAX Uint16
			MAX-ACCESS read-write
			STATUS current
			DESCRIPTION
				"FEC row delay"
		::= { ste2022c01v1Entry 71 }

		-- 1.3.6.1.4.1.10106.3.101291.1.1.73
		ste2022c01v1Tx1ColDelay OBJECT-TYPE
			SYNTAX Uint16
			MAX-ACCESS read-write
			STATUS current
			DESCRIPTION
				"FEC column delay"
		::= { ste2022c01v1Entry 73 }

		-- 1.3.6.1.4.1.10106.3.101291.1.1.75
		ste2022c01v1TxIp1SrAdd3 OBJECT-TYPE
			SYNTAX Uint8
			MAX-ACCESS read-write
			STATUS current
			DESCRIPTION
				"Source IP address (3)"
		::= { ste2022c01v1Entry 75 }

		-- 1.3.6.1.4.1.10106.3.101291.1.1.77
		ste2022c01v1TxIp1SrAdd2 OBJECT-TYPE
			SYNTAX Uint8
			MAX-ACCESS read-write
			STATUS current
			DESCRIPTION
				"Source IP address (2)"
		::= { ste2022c01v1Entry 77 }

		-- 1.3.6.1.4.1.10106.3.101291.1.1.79
		ste2022c01v1TxIp1SrAdd1 OBJECT-TYPE
			SYNTAX Uint8
			MAX-ACCESS read-write
			STATUS current
			DESCRIPTION
				"Source IP address (1)"
		::= { ste2022c01v1Entry 79 }

		-- 1.3.6.1.4.1.10106.3.101291.1.1.81
		ste2022c01v1TxIp1SrAdd0 OBJECT-TYPE
			SYNTAX Uint8
			MAX-ACCESS read-write
			STATUS current
			DESCRIPTION
				"Source IP address (0)"
		::= { ste2022c01v1Entry 81 }

		-- 1.3.6.1.4.1.10106.3.101291.1.1.83
		ste2022c01v1TxIp1SrMsk0 OBJECT-TYPE
			SYNTAX Uint8
			MAX-ACCESS read-write
			STATUS current
			DESCRIPTION
				"Source IP address mask (3)"
		::= { ste2022c01v1Entry 83 }

		-- 1.3.6.1.4.1.10106.3.101291.1.1.85
		ste2022c01v1TxIp1SrMsk1 OBJECT-TYPE
			SYNTAX Uint8
			MAX-ACCESS read-write
			STATUS current
			DESCRIPTION
				"Source IP address mask (2)"
		::= { ste2022c01v1Entry 85 }

		-- 1.3.6.1.4.1.10106.3.101291.1.1.87
		ste2022c01v1TxIp1SrMsk2 OBJECT-TYPE
			SYNTAX Uint8
			MAX-ACCESS read-write
			STATUS current
			DESCRIPTION
				"Source IP address mask (1)"
		::= { ste2022c01v1Entry 87 }

		-- 1.3.6.1.4.1.10106.3.101291.1.1.89
		ste2022c01v1TxIp1SrMsk3 OBJECT-TYPE
			SYNTAX Uint8
			MAX-ACCESS read-write
			STATUS current
			DESCRIPTION
				"Source IP address mask (0)"
		::= { ste2022c01v1Entry 89 }

		-- 1.3.6.1.4.1.10106.3.101291.1.1.91
		ste2022c01v1Tx2UniEna OBJECT-TYPE
			SYNTAX Bit0No1Yes
			MAX-ACCESS read-write
			STATUS current
			DESCRIPTION
				"Enable TX"
		::= { ste2022c01v1Entry 91 }

		-- 1.3.6.1.4.1.10106.3.101291.1.1.93
		ste2022c01v1Tx2MultiEna OBJECT-TYPE
			SYNTAX IpaTxMode
			MAX-ACCESS read-write
			STATUS current
			DESCRIPTION
				"TX mode"
		::= { ste2022c01v1Entry 93 }

		-- 1.3.6.1.4.1.10106.3.101291.1.1.95
		ste2022c01v1Tx2FecMode OBJECT-TYPE
			SYNTAX FecModeSte
			MAX-ACCESS read-write
			STATUS current
			DESCRIPTION
				"Protocol"
		::= { ste2022c01v1Entry 95 }

		-- 1.3.6.1.4.1.10106.3.101291.1.1.97
		ste2022c01v1TimestampCf2 OBJECT-TYPE
			SYNTAX Bit0No1Yes
			MAX-ACCESS read-write
			STATUS current
			DESCRIPTION
				"Timestamp insertion (SMPTE2022 header)"
		::= { ste2022c01v1Entry 97 }

		-- 1.3.6.1.4.1.10106.3.101291.1.1.99
		ste2022c01v1Tx2UipAdd3 OBJECT-TYPE
			SYNTAX Uint8
			MAX-ACCESS read-write
			STATUS current
			DESCRIPTION
				"Destination IP address (3)"
		::= { ste2022c01v1Entry 99 }

		-- 1.3.6.1.4.1.10106.3.101291.1.1.101
		ste2022c01v1Tx2UipAdd2 OBJECT-TYPE
			SYNTAX Uint8
			MAX-ACCESS read-write
			STATUS current
			DESCRIPTION
				"Destination IP address (2)"
		::= { ste2022c01v1Entry 101 }

		-- 1.3.6.1.4.1.10106.3.101291.1.1.103
		ste2022c01v1Tx2UipAdd1 OBJECT-TYPE
			SYNTAX Uint8
			MAX-ACCESS read-write
			STATUS current
			DESCRIPTION
				"Destination IP address (1)"
		::= { ste2022c01v1Entry 103 }

		-- 1.3.6.1.4.1.10106.3.101291.1.1.105
		ste2022c01v1Tx2UipAdd0 OBJECT-TYPE
			SYNTAX Uint8
			MAX-ACCESS read-write
			STATUS current
			DESCRIPTION
				"Destination IP address (0)"
		::= { ste2022c01v1Entry 105 }

		-- 1.3.6.1.4.1.10106.3.101291.1.1.107
		ste2022c01v1Tx2MipAdd3 OBJECT-TYPE
			SYNTAX Uint8
			MAX-ACCESS read-write
			STATUS current
			DESCRIPTION
				"Multicast dest. IP address (3)"
		::= { ste2022c01v1Entry 107 }

		-- 1.3.6.1.4.1.10106.3.101291.1.1.109
		ste2022c01v1Tx2MipAdd2 OBJECT-TYPE
			SYNTAX Uint8
			MAX-ACCESS read-write
			STATUS current
			DESCRIPTION
				"Multicast dest. IP address (2)"
		::= { ste2022c01v1Entry 109 }

		-- 1.3.6.1.4.1.10106.3.101291.1.1.111
		ste2022c01v1Tx2MipAdd1 OBJECT-TYPE
			SYNTAX Uint8
			MAX-ACCESS read-write
			STATUS current
			DESCRIPTION
				"Multicast dest. IP address (1)"
		::= { ste2022c01v1Entry 111 }

		-- 1.3.6.1.4.1.10106.3.101291.1.1.113
		ste2022c01v1Tx2MipAdd0 OBJECT-TYPE
			SYNTAX Uint8
			MAX-ACCESS read-write
			STATUS current
			DESCRIPTION
				"Multicast dest. IP address (0)"
		::= { ste2022c01v1Entry 113 }

		-- 1.3.6.1.4.1.10106.3.101291.1.1.115
		ste2022c01v1Tx2SPort OBJECT-TYPE
			SYNTAX Uint16
			MAX-ACCESS read-write
			STATUS current
			DESCRIPTION
				"Source port"
		::= { ste2022c01v1Entry 115 }

		-- 1.3.6.1.4.1.10106.3.101291.1.1.117
		ste2022c01v1Tx2DPort OBJECT-TYPE
			SYNTAX Uint16
			MAX-ACCESS read-write
			STATUS current
			DESCRIPTION
				"Destination port"
		::= { ste2022c01v1Entry 117 }

		-- 1.3.6.1.4.1.10106.3.101291.1.1.119
		ste2022c01v1Tx2LParam OBJECT-TYPE
			SYNTAX Uint8
			MAX-ACCESS read-write
			STATUS current
			DESCRIPTION
				"L parameter (FEC mode columns)"
		::= { ste2022c01v1Entry 119 }

		-- 1.3.6.1.4.1.10106.3.101291.1.1.121
		ste2022c01v1Tx2DParam OBJECT-TYPE
			SYNTAX Uint8
			MAX-ACCESS read-write
			STATUS current
			DESCRIPTION
				"D parameter (FEC mode rows)"
		::= { ste2022c01v1Entry 121 }

		-- 1.3.6.1.4.1.10106.3.101291.1.1.123
		ste2022c01v1Tx2RowDelay OBJECT-TYPE
			SYNTAX Uint16
			MAX-ACCESS read-write
			STATUS current
			DESCRIPTION
				"FEC row delay"
		::= { ste2022c01v1Entry 123 }

		-- 1.3.6.1.4.1.10106.3.101291.1.1.125
		ste2022c01v1Tx2ColDelay OBJECT-TYPE
			SYNTAX Uint16
			MAX-ACCESS read-write
			STATUS current
			DESCRIPTION
				"FEC column delay"
		::= { ste2022c01v1Entry 125 }

		-- 1.3.6.1.4.1.10106.3.101291.1.1.127
		ste2022c01v1TxIp2SrAdd3 OBJECT-TYPE
			SYNTAX Uint8
			MAX-ACCESS read-write
			STATUS current
			DESCRIPTION
				"Source IP address (3)"
		::= { ste2022c01v1Entry 127 }

		-- 1.3.6.1.4.1.10106.3.101291.1.1.129
		ste2022c01v1TxIp2SrAdd2 OBJECT-TYPE
			SYNTAX Uint8
			MAX-ACCESS read-write
			STATUS current
			DESCRIPTION
				"Source IP address (2)"
		::= { ste2022c01v1Entry 129 }

		-- 1.3.6.1.4.1.10106.3.101291.1.1.131
		ste2022c01v1TxIp2SrAdd1 OBJECT-TYPE
			SYNTAX Uint8
			MAX-ACCESS read-write
			STATUS current
			DESCRIPTION
				"Source IP address (1)"
		::= { ste2022c01v1Entry 131 }

		-- 1.3.6.1.4.1.10106.3.101291.1.1.133
		ste2022c01v1TxIp2SrAdd0 OBJECT-TYPE
			SYNTAX Uint8
			MAX-ACCESS read-write
			STATUS current
			DESCRIPTION
				"Source IP address (0)"
		::= { ste2022c01v1Entry 133 }

		-- 1.3.6.1.4.1.10106.3.101291.1.1.135
		ste2022c01v1TxIp2SrMsk0 OBJECT-TYPE
			SYNTAX Uint8
			MAX-ACCESS read-write
			STATUS current
			DESCRIPTION
				"Source IP address mask (3)"
		::= { ste2022c01v1Entry 135 }

		-- 1.3.6.1.4.1.10106.3.101291.1.1.137
		ste2022c01v1TxIp2SrMsk1 OBJECT-TYPE
			SYNTAX Uint8
			MAX-ACCESS read-write
			STATUS current
			DESCRIPTION
				"Source IP address mask (2)"
		::= { ste2022c01v1Entry 137 }

		-- 1.3.6.1.4.1.10106.3.101291.1.1.139
		ste2022c01v1TxIp2SrMsk2 OBJECT-TYPE
			SYNTAX Uint8
			MAX-ACCESS read-write
			STATUS current
			DESCRIPTION
				"Source IP address mask (1)"
		::= { ste2022c01v1Entry 139 }

		-- 1.3.6.1.4.1.10106.3.101291.1.1.141
		ste2022c01v1TxIp2SrMsk3 OBJECT-TYPE
			SYNTAX Uint8
			MAX-ACCESS read-write
			STATUS current
			DESCRIPTION
				"Source IP address mask (0)"
		::= { ste2022c01v1Entry 141 }

		-- 1.3.6.1.4.1.10106.3.101291.1.1.143
		ste2022c01v1Tx3UniEna OBJECT-TYPE
			SYNTAX Bit0No1Yes
			MAX-ACCESS read-write
			STATUS current
			DESCRIPTION
				"Enable TX"
		::= { ste2022c01v1Entry 143 }

		-- 1.3.6.1.4.1.10106.3.101291.1.1.145
		ste2022c01v1Tx3MultiEna OBJECT-TYPE
			SYNTAX IpaTxMode
			MAX-ACCESS read-write
			STATUS current
			DESCRIPTION
				"TX mode"
		::= { ste2022c01v1Entry 145 }

		-- 1.3.6.1.4.1.10106.3.101291.1.1.147
		ste2022c01v1Tx3FecMode OBJECT-TYPE
			SYNTAX FecModeSte
			MAX-ACCESS read-write
			STATUS current
			DESCRIPTION
				"Protocol"
		::= { ste2022c01v1Entry 147 }

		-- 1.3.6.1.4.1.10106.3.101291.1.1.149
		ste2022c01v1TimestampCf3 OBJECT-TYPE
			SYNTAX Bit0No1Yes
			MAX-ACCESS read-write
			STATUS current
			DESCRIPTION
				"Timestamp insertion (SMPTE2022 header)"
		::= { ste2022c01v1Entry 149 }

		-- 1.3.6.1.4.1.10106.3.101291.1.1.151
		ste2022c01v1Tx3UipAdd3 OBJECT-TYPE
			SYNTAX Uint8
			MAX-ACCESS read-write
			STATUS current
			DESCRIPTION
				"Destination IP address (3)"
		::= { ste2022c01v1Entry 151 }

		-- 1.3.6.1.4.1.10106.3.101291.1.1.153
		ste2022c01v1Tx3UipAdd2 OBJECT-TYPE
			SYNTAX Uint8
			MAX-ACCESS read-write
			STATUS current
			DESCRIPTION
				"Destination IP address (2)"
		::= { ste2022c01v1Entry 153 }

		-- 1.3.6.1.4.1.10106.3.101291.1.1.155
		ste2022c01v1Tx3UipAdd1 OBJECT-TYPE
			SYNTAX Uint8
			MAX-ACCESS read-write
			STATUS current
			DESCRIPTION
				"Destination IP address (1)"
		::= { ste2022c01v1Entry 155 }

		-- 1.3.6.1.4.1.10106.3.101291.1.1.157
		ste2022c01v1Tx3UipAdd0 OBJECT-TYPE
			SYNTAX Uint8
			MAX-ACCESS read-write
			STATUS current
			DESCRIPTION
				"Destination IP address (0)"
		::= { ste2022c01v1Entry 157 }

		-- 1.3.6.1.4.1.10106.3.101291.1.1.159
		ste2022c01v1Tx3MipAdd3 OBJECT-TYPE
			SYNTAX Uint8
			MAX-ACCESS read-write
			STATUS current
			DESCRIPTION
				"Multicast dest. IP address (3)"
		::= { ste2022c01v1Entry 159 }

		-- 1.3.6.1.4.1.10106.3.101291.1.1.161
		ste2022c01v1Tx3MipAdd2 OBJECT-TYPE
			SYNTAX Uint8
			MAX-ACCESS read-write
			STATUS current
			DESCRIPTION
				"Multicast dest. IP address (2)"
		::= { ste2022c01v1Entry 161 }

		-- 1.3.6.1.4.1.10106.3.101291.1.1.163
		ste2022c01v1Tx3MipAdd1 OBJECT-TYPE
			SYNTAX Uint8
			MAX-ACCESS read-write
			STATUS current
			DESCRIPTION
				"Multicast dest. IP address (1)"
		::= { ste2022c01v1Entry 163 }

		-- 1.3.6.1.4.1.10106.3.101291.1.1.165
		ste2022c01v1Tx3MipAdd0 OBJECT-TYPE
			SYNTAX Uint8
			MAX-ACCESS read-write
			STATUS current
			DESCRIPTION
				"Multicast dest. IP address (0)"
		::= { ste2022c01v1Entry 165 }

		-- 1.3.6.1.4.1.10106.3.101291.1.1.167
		ste2022c01v1Tx3SPort OBJECT-TYPE
			SYNTAX Uint16
			MAX-ACCESS read-write
			STATUS current
			DESCRIPTION
				"Source port"
		::= { ste2022c01v1Entry 167 }

		-- 1.3.6.1.4.1.10106.3.101291.1.1.169
		ste2022c01v1Tx3DPort OBJECT-TYPE
			SYNTAX Uint16
			MAX-ACCESS read-write
			STATUS current
			DESCRIPTION
				"Destination port"
		::= { ste2022c01v1Entry 169 }

		-- 1.3.6.1.4.1.10106.3.101291.1.1.171
		ste2022c01v1Tx3LParam OBJECT-TYPE
			SYNTAX Uint8
			MAX-ACCESS read-write
			STATUS current
			DESCRIPTION
				"L parameter (FEC mode columns)"
		::= { ste2022c01v1Entry 171 }

		-- 1.3.6.1.4.1.10106.3.101291.1.1.173
		ste2022c01v1Tx3DParam OBJECT-TYPE
			SYNTAX Uint8
			MAX-ACCESS read-write
			STATUS current
			DESCRIPTION
				"D parameter (FEC mode rows)"
		::= { ste2022c01v1Entry 173 }

		-- 1.3.6.1.4.1.10106.3.101291.1.1.175
		ste2022c01v1Tx3RowDelay OBJECT-TYPE
			SYNTAX Uint16
			MAX-ACCESS read-write
			STATUS current
			DESCRIPTION
				"FEC row delay"
		::= { ste2022c01v1Entry 175 }

		-- 1.3.6.1.4.1.10106.3.101291.1.1.177
		ste2022c01v1Tx3ColDelay OBJECT-TYPE
			SYNTAX Uint16
			MAX-ACCESS read-write
			STATUS current
			DESCRIPTION
				"FEC column delay"
		::= { ste2022c01v1Entry 177 }

		-- 1.3.6.1.4.1.10106.3.101291.1.1.179
		ste2022c01v1TxIp3SrAdd3 OBJECT-TYPE
			SYNTAX Uint8
			MAX-ACCESS read-write
			STATUS current
			DESCRIPTION
				"Source IP address (3)"
		::= { ste2022c01v1Entry 179 }

		-- 1.3.6.1.4.1.10106.3.101291.1.1.181
		ste2022c01v1TxIp3SrAdd2 OBJECT-TYPE
			SYNTAX Uint8
			MAX-ACCESS read-write
			STATUS current
			DESCRIPTION
				"Source IP address (2)"
		::= { ste2022c01v1Entry 181 }

		-- 1.3.6.1.4.1.10106.3.101291.1.1.183
		ste2022c01v1TxIp3SrAdd1 OBJECT-TYPE
			SYNTAX Uint8
			MAX-ACCESS read-write
			STATUS current
			DESCRIPTION
				"Source IP address (1)"
		::= { ste2022c01v1Entry 183 }

		-- 1.3.6.1.4.1.10106.3.101291.1.1.185
		ste2022c01v1TxIp3SrAdd0 OBJECT-TYPE
			SYNTAX Uint8
			MAX-ACCESS read-write
			STATUS current
			DESCRIPTION
				"Source IP address (0)"
		::= { ste2022c01v1Entry 185 }

		-- 1.3.6.1.4.1.10106.3.101291.1.1.187
		ste2022c01v1TxIp3SrMsk3 OBJECT-TYPE
			SYNTAX Uint8
			MAX-ACCESS read-write
			STATUS current
			DESCRIPTION
				"Source IP address mask (3)"
		::= { ste2022c01v1Entry 187 }

		-- 1.3.6.1.4.1.10106.3.101291.1.1.189
		ste2022c01v1TxIp3SrMsk2 OBJECT-TYPE
			SYNTAX Uint8
			MAX-ACCESS read-write
			STATUS current
			DESCRIPTION
				"Source IP address mask (2)"
		::= { ste2022c01v1Entry 189 }

		-- 1.3.6.1.4.1.10106.3.101291.1.1.191
		ste2022c01v1TxIp3SrMsk1 OBJECT-TYPE
			SYNTAX Uint8
			MAX-ACCESS read-write
			STATUS current
			DESCRIPTION
				"Source IP address mask (1)"
		::= { ste2022c01v1Entry 191 }

		-- 1.3.6.1.4.1.10106.3.101291.1.1.193
		ste2022c01v1TxIp3SrMsk0 OBJECT-TYPE
			SYNTAX Uint8
			MAX-ACCESS read-write
			STATUS current
			DESCRIPTION
				"Source IP address mask (0)"
		::= { ste2022c01v1Entry 193 }

		-- 1.3.6.1.4.1.10106.3.101291.1.1.195
		ste2022c01v1Tx4UniEna OBJECT-TYPE
			SYNTAX Bit0No1Yes
			MAX-ACCESS read-write
			STATUS current
			DESCRIPTION
				"Enable TX"
		::= { ste2022c01v1Entry 195 }

		-- 1.3.6.1.4.1.10106.3.101291.1.1.197
		ste2022c01v1Tx4MultiEna OBJECT-TYPE
			SYNTAX IpaTxMode
			MAX-ACCESS read-write
			STATUS current
			DESCRIPTION
				"TX mode"
		::= { ste2022c01v1Entry 197 }

		-- 1.3.6.1.4.1.10106.3.101291.1.1.199
		ste2022c01v1Tx4FecMode OBJECT-TYPE
			SYNTAX FecModeSte
			MAX-ACCESS read-write
			STATUS current
			DESCRIPTION
				"Protocol"
		::= { ste2022c01v1Entry 199 }

		-- 1.3.6.1.4.1.10106.3.101291.1.1.201
		ste2022c01v1TimestampCf4 OBJECT-TYPE
			SYNTAX Bit0No1Yes
			MAX-ACCESS read-write
			STATUS current
			DESCRIPTION
				"Timestamp insertion (SMPTE2022 header)"
		::= { ste2022c01v1Entry 201 }

		-- 1.3.6.1.4.1.10106.3.101291.1.1.203
		ste2022c01v1Tx4UipAdd3 OBJECT-TYPE
			SYNTAX Uint8
			MAX-ACCESS read-write
			STATUS current
			DESCRIPTION
				"Destination IP address (3)"
		::= { ste2022c01v1Entry 203 }

		-- 1.3.6.1.4.1.10106.3.101291.1.1.205
		ste2022c01v1Tx4UipAdd2 OBJECT-TYPE
			SYNTAX Uint8
			MAX-ACCESS read-write
			STATUS current
			DESCRIPTION
				"Destination IP address (2)"
		::= { ste2022c01v1Entry 205 }

		-- 1.3.6.1.4.1.10106.3.101291.1.1.207
		ste2022c01v1Tx4UipAdd1 OBJECT-TYPE
			SYNTAX Uint8
			MAX-ACCESS read-write
			STATUS current
			DESCRIPTION
				"Destination IP address (1)"
		::= { ste2022c01v1Entry 207 }

		-- 1.3.6.1.4.1.10106.3.101291.1.1.209
		ste2022c01v1Tx4UipAdd0 OBJECT-TYPE
			SYNTAX Uint8
			MAX-ACCESS read-write
			STATUS current
			DESCRIPTION
				"Destination IP address (0)"
		::= { ste2022c01v1Entry 209 }

		-- 1.3.6.1.4.1.10106.3.101291.1.1.211
		ste2022c01v1Tx4MipAdd3 OBJECT-TYPE
			SYNTAX Uint8
			MAX-ACCESS read-write
			STATUS current
			DESCRIPTION
				"Multicast dest. IP address (3)"
		::= { ste2022c01v1Entry 211 }

		-- 1.3.6.1.4.1.10106.3.101291.1.1.213
		ste2022c01v1Tx4MipAdd2 OBJECT-TYPE
			SYNTAX Uint8
			MAX-ACCESS read-write
			STATUS current
			DESCRIPTION
				"Multicast dest. IP address (2)"
		::= { ste2022c01v1Entry 213 }

		-- 1.3.6.1.4.1.10106.3.101291.1.1.215
		ste2022c01v1Tx4MipAdd1 OBJECT-TYPE
			SYNTAX Uint8
			MAX-ACCESS read-write
			STATUS current
			DESCRIPTION
				"Multicast dest. IP address (1)"
		::= { ste2022c01v1Entry 215 }

		-- 1.3.6.1.4.1.10106.3.101291.1.1.217
		ste2022c01v1Tx4MipAdd0 OBJECT-TYPE
			SYNTAX Uint8
			MAX-ACCESS read-write
			STATUS current
			DESCRIPTION
				"Multicast dest. IP address (0)"
		::= { ste2022c01v1Entry 217 }

		-- 1.3.6.1.4.1.10106.3.101291.1.1.219
		ste2022c01v1Tx4SPort OBJECT-TYPE
			SYNTAX Uint16
			MAX-ACCESS read-write
			STATUS current
			DESCRIPTION
				"Source port"
		::= { ste2022c01v1Entry 219 }

		-- 1.3.6.1.4.1.10106.3.101291.1.1.221
		ste2022c01v1Tx4DPort OBJECT-TYPE
			SYNTAX Uint16
			MAX-ACCESS read-write
			STATUS current
			DESCRIPTION
				"Destination port"
		::= { ste2022c01v1Entry 221 }

		-- 1.3.6.1.4.1.10106.3.101291.1.1.223
		ste2022c01v1Tx4LParam OBJECT-TYPE
			SYNTAX Uint8
			MAX-ACCESS read-write
			STATUS current
			DESCRIPTION
				"L parameter (FEC mode columns)"
		::= { ste2022c01v1Entry 223 }

		-- 1.3.6.1.4.1.10106.3.101291.1.1.225
		ste2022c01v1Tx4DParam OBJECT-TYPE
			SYNTAX Uint8
			MAX-ACCESS read-write
			STATUS current
			DESCRIPTION
				"D parameter (FEC mode rows)"
		::= { ste2022c01v1Entry 225 }

		-- 1.3.6.1.4.1.10106.3.101291.1.1.227
		ste2022c01v1Tx4RowDelay OBJECT-TYPE
			SYNTAX Uint16
			MAX-ACCESS read-write
			STATUS current
			DESCRIPTION
				"FEC row delay"
		::= { ste2022c01v1Entry 227 }

		-- 1.3.6.1.4.1.10106.3.101291.1.1.229
		ste2022c01v1Tx4ColDelay OBJECT-TYPE
			SYNTAX Uint16
			MAX-ACCESS read-write
			STATUS current
			DESCRIPTION
				"FEC column delay"
		::= { ste2022c01v1Entry 229 }

		-- 1.3.6.1.4.1.10106.3.101291.1.1.231
		ste2022c01v1TxIp4SrAdd3 OBJECT-TYPE
			SYNTAX Uint8
			MAX-ACCESS read-write
			STATUS current
			DESCRIPTION
				"Source IP address (3)"
		::= { ste2022c01v1Entry 231 }

		-- 1.3.6.1.4.1.10106.3.101291.1.1.233
		ste2022c01v1TxIp4SrAdd2 OBJECT-TYPE
			SYNTAX Uint8
			MAX-ACCESS read-write
			STATUS current
			DESCRIPTION
				"Source IP address (2)"
		::= { ste2022c01v1Entry 233 }

		-- 1.3.6.1.4.1.10106.3.101291.1.1.235
		ste2022c01v1TxIp4SrAdd1 OBJECT-TYPE
			SYNTAX Uint8
			MAX-ACCESS read-write
			STATUS current
			DESCRIPTION
				"Source IP address (1)"
		::= { ste2022c01v1Entry 235 }

		-- 1.3.6.1.4.1.10106.3.101291.1.1.237
		ste2022c01v1TxIp4SrAdd0 OBJECT-TYPE
			SYNTAX Uint8
			MAX-ACCESS read-write
			STATUS current
			DESCRIPTION
				"Source IP address (0)"
		::= { ste2022c01v1Entry 237 }

		-- 1.3.6.1.4.1.10106.3.101291.1.1.239
		ste2022c01v1TxIp4SrMsk3 OBJECT-TYPE
			SYNTAX Uint8
			MAX-ACCESS read-write
			STATUS current
			DESCRIPTION
				"Source IP address mask (3)"
		::= { ste2022c01v1Entry 239 }

		-- 1.3.6.1.4.1.10106.3.101291.1.1.241
		ste2022c01v1TxIp4SrMsk2 OBJECT-TYPE
			SYNTAX Uint8
			MAX-ACCESS read-write
			STATUS current
			DESCRIPTION
				"Source IP address mask (2)"
		::= { ste2022c01v1Entry 241 }

		-- 1.3.6.1.4.1.10106.3.101291.1.1.243
		ste2022c01v1TxIp4SrMsk1 OBJECT-TYPE
			SYNTAX Uint8
			MAX-ACCESS read-write
			STATUS current
			DESCRIPTION
				"Source IP address mask (1)"
		::= { ste2022c01v1Entry 243 }

		-- 1.3.6.1.4.1.10106.3.101291.1.1.245
		ste2022c01v1TxIp4SrMsk0 OBJECT-TYPE
			SYNTAX Uint8
			MAX-ACCESS read-write
			STATUS current
			DESCRIPTION
				"Source IP address mask (0)"
		::= { ste2022c01v1Entry 245 }

		-- 1.3.6.1.4.1.10106.3.101291.1.1.247
		ste2022c01v1Str1Ena OBJECT-TYPE
			SYNTAX Bit0No1Yes
			MAX-ACCESS read-write
			STATUS current
			DESCRIPTION
				"Receiver enable"
		::= { ste2022c01v1Entry 247 }

		-- 1.3.6.1.4.1.10106.3.101291.1.1.249
		ste2022c01v1Str1MulticEna OBJECT-TYPE
			SYNTAX IpaTxMode
			MAX-ACCESS read-write
			STATUS current
			DESCRIPTION
				"RX mode"
		::= { ste2022c01v1Entry 249 }

		-- 1.3.6.1.4.1.10106.3.101291.1.1.251
		ste2022c01v1Str1FecEna OBJECT-TYPE
			SYNTAX Bit0No1Yes
			MAX-ACCESS read-write
			STATUS current
			DESCRIPTION
				"Enable FEC"
		::= { ste2022c01v1Entry 251 }

		-- 1.3.6.1.4.1.10106.3.101291.1.1.253
		ste2022c01v1Str1UipDAdd3 OBJECT-TYPE
			SYNTAX Uint8
			MAX-ACCESS read-write
			STATUS current
			DESCRIPTION
				"IP address (3)"
		::= { ste2022c01v1Entry 253 }

		-- 1.3.6.1.4.1.10106.3.101291.1.1.255
		ste2022c01v1Str1UipDAdd2 OBJECT-TYPE
			SYNTAX Uint8
			MAX-ACCESS read-write
			STATUS current
			DESCRIPTION
				"IP address (2)"
		::= { ste2022c01v1Entry 255 }

		-- 1.3.6.1.4.1.10106.3.101291.1.1.257
		ste2022c01v1Str1UipDAdd1 OBJECT-TYPE
			SYNTAX Uint8
			MAX-ACCESS read-write
			STATUS current
			DESCRIPTION
				"IP address (1)"
		::= { ste2022c01v1Entry 257 }

		-- 1.3.6.1.4.1.10106.3.101291.1.1.259
		ste2022c01v1Str1UipDAdd0 OBJECT-TYPE
			SYNTAX Uint8
			MAX-ACCESS read-write
			STATUS current
			DESCRIPTION
				"IP address (0)"
		::= { ste2022c01v1Entry 259 }

		-- 1.3.6.1.4.1.10106.3.101291.1.1.261
		ste2022c01v1Str1MipDAdd3 OBJECT-TYPE
			SYNTAX Uint8
			MAX-ACCESS read-write
			STATUS current
			DESCRIPTION
				"Multicast IP address (3)"
		::= { ste2022c01v1Entry 261 }

		-- 1.3.6.1.4.1.10106.3.101291.1.1.263
		ste2022c01v1Str1MipDAdd2 OBJECT-TYPE
			SYNTAX Uint8
			MAX-ACCESS read-write
			STATUS current
			DESCRIPTION
				"Multicast IP address (2)"
		::= { ste2022c01v1Entry 263 }

		-- 1.3.6.1.4.1.10106.3.101291.1.1.265
		ste2022c01v1Str1MipDAdd1 OBJECT-TYPE
			SYNTAX Uint8
			MAX-ACCESS read-write
			STATUS current
			DESCRIPTION
				"Multicast IP address (1)"
		::= { ste2022c01v1Entry 265 }

		-- 1.3.6.1.4.1.10106.3.101291.1.1.267
		ste2022c01v1Str1MipDAdd0 OBJECT-TYPE
			SYNTAX Uint8
			MAX-ACCESS read-write
			STATUS current
			DESCRIPTION
				"Multicast IP address (0)"
		::= { ste2022c01v1Entry 267 }

		-- 1.3.6.1.4.1.10106.3.101291.1.1.269
		ste2022c01v1Str1IgmFAdd3 OBJECT-TYPE
			SYNTAX Uint8
			MAX-ACCESS read-write
			STATUS current
			DESCRIPTION
				"Source IP address (3)"
		::= { ste2022c01v1Entry 269 }

		-- 1.3.6.1.4.1.10106.3.101291.1.1.271
		ste2022c01v1Str1IgmFAdd2 OBJECT-TYPE
			SYNTAX Uint8
			MAX-ACCESS read-write
			STATUS current
			DESCRIPTION
				"Source IP address (2)"
		::= { ste2022c01v1Entry 271 }

		-- 1.3.6.1.4.1.10106.3.101291.1.1.273
		ste2022c01v1Str1IgmFAdd1 OBJECT-TYPE
			SYNTAX Uint8
			MAX-ACCESS read-write
			STATUS current
			DESCRIPTION
				"Source IP address (1)"
		::= { ste2022c01v1Entry 273 }

		-- 1.3.6.1.4.1.10106.3.101291.1.1.275
		ste2022c01v1Str1IgmFAdd0 OBJECT-TYPE
			SYNTAX Uint8
			MAX-ACCESS read-write
			STATUS current
			DESCRIPTION
				"Source IP address (0)"
		::= { ste2022c01v1Entry 275 }

		-- 1.3.6.1.4.1.10106.3.101291.1.1.277
		ste2022c01v1Str1DPort OBJECT-TYPE
			SYNTAX Uint16
			MAX-ACCESS read-write
			STATUS current
			DESCRIPTION
				"Destination port"
		::= { ste2022c01v1Entry 277 }

		-- 1.3.6.1.4.1.10106.3.101291.1.1.279
		ste2022c01v1RxIp1SrMsk OBJECT-TYPE
			SYNTAX Uint8
			MAX-ACCESS read-write
			STATUS current
			DESCRIPTION
				"IP address mask (3)"
		::= { ste2022c01v1Entry 279 }

		-- 1.3.6.1.4.1.10106.3.101291.1.1.281
		ste2022c01v1RxIp1SrMsk2 OBJECT-TYPE
			SYNTAX Uint8
			MAX-ACCESS read-write
			STATUS current
			DESCRIPTION
				"IP address mask (2)"
		::= { ste2022c01v1Entry 281 }

		-- 1.3.6.1.4.1.10106.3.101291.1.1.283
		ste2022c01v1RxIp1SrMsk1 OBJECT-TYPE
			SYNTAX Uint8
			MAX-ACCESS read-write
			STATUS current
			DESCRIPTION
				"IP address mask (1)"
		::= { ste2022c01v1Entry 283 }

		-- 1.3.6.1.4.1.10106.3.101291.1.1.285
		ste2022c01v1RxIp1SrMsk0 OBJECT-TYPE
			SYNTAX Uint8
			MAX-ACCESS read-write
			STATUS current
			DESCRIPTION
				"IP address mask (0)"
		::= { ste2022c01v1Entry 285 }

		-- 1.3.6.1.4.1.10106.3.101291.1.1.287
		ste2022c01v1Str2Ena OBJECT-TYPE
			SYNTAX Bit0No1Yes
			MAX-ACCESS read-write
			STATUS current
			DESCRIPTION
				"Receiver enable"
		::= { ste2022c01v1Entry 287 }

		-- 1.3.6.1.4.1.10106.3.101291.1.1.289
		ste2022c01v1Str2MulticEna OBJECT-TYPE
			SYNTAX IpaTxMode
			MAX-ACCESS read-write
			STATUS current
			DESCRIPTION
				"RX mode"
		::= { ste2022c01v1Entry 289 }

		-- 1.3.6.1.4.1.10106.3.101291.1.1.291
		ste2022c01v1Str2FecEna OBJECT-TYPE
			SYNTAX Bit0No1Yes
			MAX-ACCESS read-write
			STATUS current
			DESCRIPTION
				"Enable FEC"
		::= { ste2022c01v1Entry 291 }

		-- 1.3.6.1.4.1.10106.3.101291.1.1.293
		ste2022c01v1Str2UipDAdd3 OBJECT-TYPE
			SYNTAX Uint8
			MAX-ACCESS read-write
			STATUS current
			DESCRIPTION
				"IP address (3)"
		::= { ste2022c01v1Entry 293 }

		-- 1.3.6.1.4.1.10106.3.101291.1.1.295
		ste2022c01v1Str2UipDAdd2 OBJECT-TYPE
			SYNTAX Uint8
			MAX-ACCESS read-write
			STATUS current
			DESCRIPTION
				"IP address (2)"
		::= { ste2022c01v1Entry 295 }

		-- 1.3.6.1.4.1.10106.3.101291.1.1.297
		ste2022c01v1Str2UipDAdd1 OBJECT-TYPE
			SYNTAX Uint8
			MAX-ACCESS read-write
			STATUS current
			DESCRIPTION
				"IP address (1)"
		::= { ste2022c01v1Entry 297 }

		-- 1.3.6.1.4.1.10106.3.101291.1.1.299
		ste2022c01v1Str2UipDAdd0 OBJECT-TYPE
			SYNTAX Uint8
			MAX-ACCESS read-write
			STATUS current
			DESCRIPTION
				"IP address (0)"
		::= { ste2022c01v1Entry 299 }

		-- 1.3.6.1.4.1.10106.3.101291.1.1.301
		ste2022c01v1Str2MipDAdd3 OBJECT-TYPE
			SYNTAX Uint8
			MAX-ACCESS read-write
			STATUS current
			DESCRIPTION
				"Multicast IP address (3)"
		::= { ste2022c01v1Entry 301 }

		-- 1.3.6.1.4.1.10106.3.101291.1.1.303
		ste2022c01v1Str2MipDAdd2 OBJECT-TYPE
			SYNTAX Uint8
			MAX-ACCESS read-write
			STATUS current
			DESCRIPTION
				"Multicast IP address (2)"
		::= { ste2022c01v1Entry 303 }

		-- 1.3.6.1.4.1.10106.3.101291.1.1.305
		ste2022c01v1Str2MipDAdd1 OBJECT-TYPE
			SYNTAX Uint8
			MAX-ACCESS read-write
			STATUS current
			DESCRIPTION
				"Multicast IP address (1)"
		::= { ste2022c01v1Entry 305 }

		-- 1.3.6.1.4.1.10106.3.101291.1.1.307
		ste2022c01v1Str2MipDAdd0 OBJECT-TYPE
			SYNTAX Uint8
			MAX-ACCESS read-write
			STATUS current
			DESCRIPTION
				"Multicast IP address (0)"
		::= { ste2022c01v1Entry 307 }

		-- 1.3.6.1.4.1.10106.3.101291.1.1.309
		ste2022c01v1Str2IgmFAdd3 OBJECT-TYPE
			SYNTAX Uint8
			MAX-ACCESS read-write
			STATUS current
			DESCRIPTION
				"Source IP address (3)"
		::= { ste2022c01v1Entry 309 }

		-- 1.3.6.1.4.1.10106.3.101291.1.1.311
		ste2022c01v1Str2IgmFAdd2 OBJECT-TYPE
			SYNTAX Uint8
			MAX-ACCESS read-write
			STATUS current
			DESCRIPTION
				"Source IP address (2)"
		::= { ste2022c01v1Entry 311 }

		-- 1.3.6.1.4.1.10106.3.101291.1.1.313
		ste2022c01v1Str2IgmFAdd1 OBJECT-TYPE
			SYNTAX Uint8
			MAX-ACCESS read-write
			STATUS current
			DESCRIPTION
				"Source IP address (1)"
		::= { ste2022c01v1Entry 313 }

		-- 1.3.6.1.4.1.10106.3.101291.1.1.315
		ste2022c01v1Str2IgmFAdd0 OBJECT-TYPE
			SYNTAX Uint8
			MAX-ACCESS read-write
			STATUS current
			DESCRIPTION
				"Source IP address (0)"
		::= { ste2022c01v1Entry 315 }

		-- 1.3.6.1.4.1.10106.3.101291.1.1.317
		ste2022c01v1Str2DPort OBJECT-TYPE
			SYNTAX Uint16
			MAX-ACCESS read-write
			STATUS current
			DESCRIPTION
				"Destination port"
		::= { ste2022c01v1Entry 317 }

		-- 1.3.6.1.4.1.10106.3.101291.1.1.319
		ste2022c01v1RxIp2SrMsk OBJECT-TYPE
			SYNTAX Uint8
			MAX-ACCESS read-write
			STATUS current
			DESCRIPTION
				"IP address mask (3)"
		::= { ste2022c01v1Entry 319 }

		-- 1.3.6.1.4.1.10106.3.101291.1.1.321
		ste2022c01v1RxIp2SrMsk1 OBJECT-TYPE
			SYNTAX Uint8
			MAX-ACCESS read-write
			STATUS current
			DESCRIPTION
				"IP address mask (2)"
		::= { ste2022c01v1Entry 321 }

		-- 1.3.6.1.4.1.10106.3.101291.1.1.323
		ste2022c01v1RxIp2SrMsk2 OBJECT-TYPE
			SYNTAX Uint8
			MAX-ACCESS read-write
			STATUS current
			DESCRIPTION
				"IP address mask (1)"
		::= { ste2022c01v1Entry 323 }

		-- 1.3.6.1.4.1.10106.3.101291.1.1.325
		ste2022c01v1RxIp2SrMsk3 OBJECT-TYPE
			SYNTAX Uint8
			MAX-ACCESS read-write
			STATUS current
			DESCRIPTION
				"IP address mask (0)"
		::= { ste2022c01v1Entry 325 }

		-- 1.3.6.1.4.1.10106.3.101291.1.1.327
		ste2022c01v1Str3Ena OBJECT-TYPE
			SYNTAX Bit0No1Yes
			MAX-ACCESS read-write
			STATUS current
			DESCRIPTION
				"Receiver enable"
		::= { ste2022c01v1Entry 327 }

		-- 1.3.6.1.4.1.10106.3.101291.1.1.329
		ste2022c01v1Str3MulticEna OBJECT-TYPE
			SYNTAX IpaTxMode
			MAX-ACCESS read-write
			STATUS current
			DESCRIPTION
				"RX mode"
		::= { ste2022c01v1Entry 329 }

		-- 1.3.6.1.4.1.10106.3.101291.1.1.331
		ste2022c01v1Str3FecEna OBJECT-TYPE
			SYNTAX Bit0No1Yes
			MAX-ACCESS read-write
			STATUS current
			DESCRIPTION
				"Enable FEC"
		::= { ste2022c01v1Entry 331 }

		-- 1.3.6.1.4.1.10106.3.101291.1.1.333
		ste2022c01v1Str3UipDAdd3 OBJECT-TYPE
			SYNTAX Uint8
			MAX-ACCESS read-write
			STATUS current
			DESCRIPTION
				"IP address (3)"
		::= { ste2022c01v1Entry 333 }

		-- 1.3.6.1.4.1.10106.3.101291.1.1.335
		ste2022c01v1Str3UipDAdd2 OBJECT-TYPE
			SYNTAX Uint8
			MAX-ACCESS read-write
			STATUS current
			DESCRIPTION
				"IP address (2)"
		::= { ste2022c01v1Entry 335 }

		-- 1.3.6.1.4.1.10106.3.101291.1.1.337
		ste2022c01v1Str3UipDAdd1 OBJECT-TYPE
			SYNTAX Uint8
			MAX-ACCESS read-write
			STATUS current
			DESCRIPTION
				"IP address (1)"
		::= { ste2022c01v1Entry 337 }

		-- 1.3.6.1.4.1.10106.3.101291.1.1.339
		ste2022c01v1Str3UipDAdd0 OBJECT-TYPE
			SYNTAX Uint8
			MAX-ACCESS read-write
			STATUS current
			DESCRIPTION
				"IP address (0)"
		::= { ste2022c01v1Entry 339 }

		-- 1.3.6.1.4.1.10106.3.101291.1.1.341
		ste2022c01v1Str3MipDAdd3 OBJECT-TYPE
			SYNTAX Uint8
			MAX-ACCESS read-write
			STATUS current
			DESCRIPTION
				"Multicast IP address (3)"
		::= { ste2022c01v1Entry 341 }

		-- 1.3.6.1.4.1.10106.3.101291.1.1.343
		ste2022c01v1Str3MipDAdd2 OBJECT-TYPE
			SYNTAX Uint8
			MAX-ACCESS read-write
			STATUS current
			DESCRIPTION
				"Multicast IP address (2)"
		::= { ste2022c01v1Entry 343 }

		-- 1.3.6.1.4.1.10106.3.101291.1.1.345
		ste2022c01v1Str3MipDAdd1 OBJECT-TYPE
			SYNTAX Uint8
			MAX-ACCESS read-write
			STATUS current
			DESCRIPTION
				"Multicast IP address (1)"
		::= { ste2022c01v1Entry 345 }

		-- 1.3.6.1.4.1.10106.3.101291.1.1.347
		ste2022c01v1Str3MipDAdd0 OBJECT-TYPE
			SYNTAX Uint8
			MAX-ACCESS read-write
			STATUS current
			DESCRIPTION
				"Multicast IP address (0)"
		::= { ste2022c01v1Entry 347 }

		-- 1.3.6.1.4.1.10106.3.101291.1.1.349
		ste2022c01v1Str3IgmFAdd3 OBJECT-TYPE
			SYNTAX Uint8
			MAX-ACCESS read-write
			STATUS current
			DESCRIPTION
				"Source IP address (3)"
		::= { ste2022c01v1Entry 349 }

		-- 1.3.6.1.4.1.10106.3.101291.1.1.351
		ste2022c01v1Str3IgmFAdd2 OBJECT-TYPE
			SYNTAX Uint8
			MAX-ACCESS read-write
			STATUS current
			DESCRIPTION
				"Source IP address (2)"
		::= { ste2022c01v1Entry 351 }

		-- 1.3.6.1.4.1.10106.3.101291.1.1.353
		ste2022c01v1Str3IgmFAdd1 OBJECT-TYPE
			SYNTAX Uint8
			MAX-ACCESS read-write
			STATUS current
			DESCRIPTION
				"Source IP address (1)"
		::= { ste2022c01v1Entry 353 }

		-- 1.3.6.1.4.1.10106.3.101291.1.1.355
		ste2022c01v1Str3IgmFAdd0 OBJECT-TYPE
			SYNTAX Uint8
			MAX-ACCESS read-write
			STATUS current
			DESCRIPTION
				"Source IP address (0)"
		::= { ste2022c01v1Entry 355 }

		-- 1.3.6.1.4.1.10106.3.101291.1.1.357
		ste2022c01v1Str3DPort OBJECT-TYPE
			SYNTAX Uint16
			MAX-ACCESS read-write
			STATUS current
			DESCRIPTION
				"Destination port"
		::= { ste2022c01v1Entry 357 }

		-- 1.3.6.1.4.1.10106.3.101291.1.1.359
		ste2022c01v1RxIp3SrMsk3 OBJECT-TYPE
			SYNTAX Uint8
			MAX-ACCESS read-write
			STATUS current
			DESCRIPTION
				"IP address mask (3)"
		::= { ste2022c01v1Entry 359 }

		-- 1.3.6.1.4.1.10106.3.101291.1.1.361
		ste2022c01v1RxIp3SrMsk2 OBJECT-TYPE
			SYNTAX Uint8
			MAX-ACCESS read-write
			STATUS current
			DESCRIPTION
				"IP address mask (2)"
		::= { ste2022c01v1Entry 361 }

		-- 1.3.6.1.4.1.10106.3.101291.1.1.363
		ste2022c01v1RxIp3SrMsk1 OBJECT-TYPE
			SYNTAX Uint8
			MAX-ACCESS read-write
			STATUS current
			DESCRIPTION
				"IP address mask (1)"
		::= { ste2022c01v1Entry 363 }

		-- 1.3.6.1.4.1.10106.3.101291.1.1.365
		ste2022c01v1RxIp3SrMsk0 OBJECT-TYPE
			SYNTAX Uint8
			MAX-ACCESS read-write
			STATUS current
			DESCRIPTION
				"IP address mask (0)"
		::= { ste2022c01v1Entry 365 }

		-- 1.3.6.1.4.1.10106.3.101291.1.1.367
		ste2022c01v1Str4Ena OBJECT-TYPE
			SYNTAX Bit0No1Yes
			MAX-ACCESS read-write
			STATUS current
			DESCRIPTION
				"Receiver enable"
		::= { ste2022c01v1Entry 367 }

		-- 1.3.6.1.4.1.10106.3.101291.1.1.369
		ste2022c01v1Str4MulticEna OBJECT-TYPE
			SYNTAX IpaTxMode
			MAX-ACCESS read-write
			STATUS current
			DESCRIPTION
				"RX mode"
		::= { ste2022c01v1Entry 369 }

		-- 1.3.6.1.4.1.10106.3.101291.1.1.371
		ste2022c01v1Str4FecEna OBJECT-TYPE
			SYNTAX Bit0No1Yes
			MAX-ACCESS read-write
			STATUS current
			DESCRIPTION
				"Enable FEC"
		::= { ste2022c01v1Entry 371 }

		-- 1.3.6.1.4.1.10106.3.101291.1.1.373
		ste2022c01v1Str4UipDAdd3 OBJECT-TYPE
			SYNTAX Uint8
			MAX-ACCESS read-write
			STATUS current
			DESCRIPTION
				"IP address (3)"
		::= { ste2022c01v1Entry 373 }

		-- 1.3.6.1.4.1.10106.3.101291.1.1.375
		ste2022c01v1Str4UipDAdd2 OBJECT-TYPE
			SYNTAX Uint8
			MAX-ACCESS read-write
			STATUS current
			DESCRIPTION
				"IP address (2)"
		::= { ste2022c01v1Entry 375 }

		-- 1.3.6.1.4.1.10106.3.101291.1.1.377
		ste2022c01v1Str4UipDAdd1 OBJECT-TYPE
			SYNTAX Uint8
			MAX-ACCESS read-write
			STATUS current
			DESCRIPTION
				"IP address (1)"
		::= { ste2022c01v1Entry 377 }

		-- 1.3.6.1.4.1.10106.3.101291.1.1.379
		ste2022c01v1Str4UipDAdd0 OBJECT-TYPE
			SYNTAX Uint8
			MAX-ACCESS read-write
			STATUS current
			DESCRIPTION
				"IP address (0)"
		::= { ste2022c01v1Entry 379 }

		-- 1.3.6.1.4.1.10106.3.101291.1.1.381
		ste2022c01v1Str4MipDAdd3 OBJECT-TYPE
			SYNTAX Uint8
			MAX-ACCESS read-write
			STATUS current
			DESCRIPTION
				"Multicast IP address (3)"
		::= { ste2022c01v1Entry 381 }

		-- 1.3.6.1.4.1.10106.3.101291.1.1.383
		ste2022c01v1Str4MipDAdd2 OBJECT-TYPE
			SYNTAX Uint8
			MAX-ACCESS read-write
			STATUS current
			DESCRIPTION
				"Multicast IP address (2)"
		::= { ste2022c01v1Entry 383 }

		-- 1.3.6.1.4.1.10106.3.101291.1.1.385
		ste2022c01v1Str4MipDAdd1 OBJECT-TYPE
			SYNTAX Uint8
			MAX-ACCESS read-write
			STATUS current
			DESCRIPTION
				"Multicast IP address (1)"
		::= { ste2022c01v1Entry 385 }

		-- 1.3.6.1.4.1.10106.3.101291.1.1.387
		ste2022c01v1Str4MipDAdd0 OBJECT-TYPE
			SYNTAX Uint8
			MAX-ACCESS read-write
			STATUS current
			DESCRIPTION
				"Multicast IP address (0)"
		::= { ste2022c01v1Entry 387 }

		-- 1.3.6.1.4.1.10106.3.101291.1.1.389
		ste2022c01v1Str4IgmFAdd3 OBJECT-TYPE
			SYNTAX Uint8
			MAX-ACCESS read-write
			STATUS current
			DESCRIPTION
				"Source IP address (3)"
		::= { ste2022c01v1Entry 389 }

		-- 1.3.6.1.4.1.10106.3.101291.1.1.391
		ste2022c01v1Str4IgmFAdd2 OBJECT-TYPE
			SYNTAX Uint8
			MAX-ACCESS read-write
			STATUS current
			DESCRIPTION
				"Source IP address (2)"
		::= { ste2022c01v1Entry 391 }

		-- 1.3.6.1.4.1.10106.3.101291.1.1.393
		ste2022c01v1Str4IgmFAdd1 OBJECT-TYPE
			SYNTAX Uint8
			MAX-ACCESS read-write
			STATUS current
			DESCRIPTION
				"Source IP address (1)"
		::= { ste2022c01v1Entry 393 }

		-- 1.3.6.1.4.1.10106.3.101291.1.1.395
		ste2022c01v1Str4IgmFAdd0 OBJECT-TYPE
			SYNTAX Uint8
			MAX-ACCESS read-write
			STATUS current
			DESCRIPTION
				"Source IP address (0)"
		::= { ste2022c01v1Entry 395 }

		-- 1.3.6.1.4.1.10106.3.101291.1.1.397
		ste2022c01v1Str4DPort OBJECT-TYPE
			SYNTAX Uint16
			MAX-ACCESS read-write
			STATUS current
			DESCRIPTION
				"Destination port"
		::= { ste2022c01v1Entry 397 }

		-- 1.3.6.1.4.1.10106.3.101291.1.1.399
		ste2022c01v1RxIp4SrMsk3 OBJECT-TYPE
			SYNTAX Uint8
			MAX-ACCESS read-write
			STATUS current
			DESCRIPTION
				"IP address mask (3)"
		::= { ste2022c01v1Entry 399 }

		-- 1.3.6.1.4.1.10106.3.101291.1.1.401
		ste2022c01v1RxIp4SrMsk2 OBJECT-TYPE
			SYNTAX Uint8
			MAX-ACCESS read-write
			STATUS current
			DESCRIPTION
				"IP address mask (2)"
		::= { ste2022c01v1Entry 401 }

		-- 1.3.6.1.4.1.10106.3.101291.1.1.403
		ste2022c01v1RxIp4SrMsk1 OBJECT-TYPE
			SYNTAX Uint8
			MAX-ACCESS read-write
			STATUS current
			DESCRIPTION
				"IP address mask (1)"
		::= { ste2022c01v1Entry 403 }

		-- 1.3.6.1.4.1.10106.3.101291.1.1.405
		ste2022c01v1RxIp4SrMsk0 OBJECT-TYPE
			SYNTAX Uint8
			MAX-ACCESS read-write
			STATUS current
			DESCRIPTION
				"IP address mask (0)"
		::= { ste2022c01v1Entry 405 }

		-- 1.3.6.1.4.1.10106.3.101291.1.1.407
		ste2022c01v1Rx1FecMode OBJECT-TYPE
			SYNTAX FecModeSte
			MAX-ACCESS read-only
			STATUS current
			DESCRIPTION
				"Protocol"
		::= { ste2022c01v1Entry 407 }

		-- 1.3.6.1.4.1.10106.3.101291.1.1.409
		ste2022c01v1Rx1IpRxAdd3 OBJECT-TYPE
			SYNTAX Uint8
			MAX-ACCESS read-only
			STATUS current
			DESCRIPTION
				"RX packets source IP address (3)"
		::= { ste2022c01v1Entry 409 }

		-- 1.3.6.1.4.1.10106.3.101291.1.1.411
		ste2022c01v1Rx1IpRxAdd2 OBJECT-TYPE
			SYNTAX Uint8
			MAX-ACCESS read-only
			STATUS current
			DESCRIPTION
				"RX packets source IP address (2)"
		::= { ste2022c01v1Entry 411 }

		-- 1.3.6.1.4.1.10106.3.101291.1.1.413
		ste2022c01v1Rx1IpRxAdd1 OBJECT-TYPE
			SYNTAX Uint8
			MAX-ACCESS read-only
			STATUS current
			DESCRIPTION
				"RX packets source IP address (1)"
		::= { ste2022c01v1Entry 413 }

		-- 1.3.6.1.4.1.10106.3.101291.1.1.415
		ste2022c01v1Rx1IpRxAdd0 OBJECT-TYPE
			SYNTAX Uint8
			MAX-ACCESS read-only
			STATUS current
			DESCRIPTION
				"RX packets source IP address (0)"
		::= { ste2022c01v1Entry 415 }

		-- 1.3.6.1.4.1.10106.3.101291.1.1.417
		ste2022c01v1Rx1IpRxPort OBJECT-TYPE
			SYNTAX Uint16
			MAX-ACCESS read-only
			STATUS current
			DESCRIPTION
				"RX packets UDP source port"
		::= { ste2022c01v1Entry 417 }

		-- 1.3.6.1.4.1.10106.3.101291.1.1.419
		ste2022c01v1Rx1LParam OBJECT-TYPE
			SYNTAX Uint16
			MAX-ACCESS read-only
			STATUS current
			DESCRIPTION
				"L parameter (FEC mode columns)"
		::= { ste2022c01v1Entry 419 }

		-- 1.3.6.1.4.1.10106.3.101291.1.1.421
		ste2022c01v1Rx1DParam OBJECT-TYPE
			SYNTAX Uint16
			MAX-ACCESS read-only
			STATUS current
			DESCRIPTION
				"D parameter (FEC mode rows)"
		::= { ste2022c01v1Entry 421 }

		-- 1.3.6.1.4.1.10106.3.101291.1.1.423
		ste2022c01v1Rx2FecMode OBJECT-TYPE
			SYNTAX FecModeSte
			MAX-ACCESS read-only
			STATUS current
			DESCRIPTION
				"Protocol"
		::= { ste2022c01v1Entry 423 }

		-- 1.3.6.1.4.1.10106.3.101291.1.1.425
		ste2022c01v1Rx2IpRxAdd3 OBJECT-TYPE
			SYNTAX Uint8
			MAX-ACCESS read-only
			STATUS current
			DESCRIPTION
				"RX packets source IP address (3)"
		::= { ste2022c01v1Entry 425 }

		-- 1.3.6.1.4.1.10106.3.101291.1.1.427
		ste2022c01v1Rx2IpRxAdd2 OBJECT-TYPE
			SYNTAX Uint8
			MAX-ACCESS read-only
			STATUS current
			DESCRIPTION
				"RX packets source IP address (2)"
		::= { ste2022c01v1Entry 427 }

		-- 1.3.6.1.4.1.10106.3.101291.1.1.429
		ste2022c01v1Rx2IpRxAdd1 OBJECT-TYPE
			SYNTAX Uint8
			MAX-ACCESS read-only
			STATUS current
			DESCRIPTION
				"RX packets source IP address (1)"
		::= { ste2022c01v1Entry 429 }

		-- 1.3.6.1.4.1.10106.3.101291.1.1.431
		ste2022c01v1Rx2IpRxAdd0 OBJECT-TYPE
			SYNTAX Uint8
			MAX-ACCESS read-only
			STATUS current
			DESCRIPTION
				"RX packets source IP address (0)"
		::= { ste2022c01v1Entry 431 }

		-- 1.3.6.1.4.1.10106.3.101291.1.1.433
		ste2022c01v1Rx2IpRxPort OBJECT-TYPE
			SYNTAX Uint16
			MAX-ACCESS read-only
			STATUS current
			DESCRIPTION
				"RX packets UDP source port"
		::= { ste2022c01v1Entry 433 }

		-- 1.3.6.1.4.1.10106.3.101291.1.1.435
		ste2022c01v1Rx2LParam OBJECT-TYPE
			SYNTAX Uint16
			MAX-ACCESS read-only
			STATUS current
			DESCRIPTION
				"L parameter (FEC mode columns)"
		::= { ste2022c01v1Entry 435 }

		-- 1.3.6.1.4.1.10106.3.101291.1.1.437
		ste2022c01v1Rx2DParam OBJECT-TYPE
			SYNTAX Uint16
			MAX-ACCESS read-only
			STATUS current
			DESCRIPTION
				"D parameter (FEC mode rows)"
		::= { ste2022c01v1Entry 437 }

		-- 1.3.6.1.4.1.10106.3.101291.1.1.439
		ste2022c01v1Rx3FecMode OBJECT-TYPE
			SYNTAX FecModeSte
			MAX-ACCESS read-only
			STATUS current
			DESCRIPTION
				"Protocol"
		::= { ste2022c01v1Entry 439 }

		-- 1.3.6.1.4.1.10106.3.101291.1.1.441
		ste2022c01v1Rx3IpRxAdd3 OBJECT-TYPE
			SYNTAX Uint8
			MAX-ACCESS read-only
			STATUS current
			DESCRIPTION
				"RX packets source IP address (3)"
		::= { ste2022c01v1Entry 441 }

		-- 1.3.6.1.4.1.10106.3.101291.1.1.443
		ste2022c01v1Rx3IpRxAdd2 OBJECT-TYPE
			SYNTAX Uint8
			MAX-ACCESS read-only
			STATUS current
			DESCRIPTION
				"RX packets source IP address (2)"
		::= { ste2022c01v1Entry 443 }

		-- 1.3.6.1.4.1.10106.3.101291.1.1.445
		ste2022c01v1Rx3IpRxAdd1 OBJECT-TYPE
			SYNTAX Uint8
			MAX-ACCESS read-only
			STATUS current
			DESCRIPTION
				"RX packets source IP address (1)"
		::= { ste2022c01v1Entry 445 }

		-- 1.3.6.1.4.1.10106.3.101291.1.1.447
		ste2022c01v1Rx3IpRxAdd0 OBJECT-TYPE
			SYNTAX Uint8
			MAX-ACCESS read-only
			STATUS current
			DESCRIPTION
				"RX packets source IP address (0)"
		::= { ste2022c01v1Entry 447 }

		-- 1.3.6.1.4.1.10106.3.101291.1.1.449
		ste2022c01v1Rx3IpRxPort OBJECT-TYPE
			SYNTAX Uint16
			MAX-ACCESS read-only
			STATUS current
			DESCRIPTION
				"RX packets UDP source port"
		::= { ste2022c01v1Entry 449 }

		-- 1.3.6.1.4.1.10106.3.101291.1.1.451
		ste2022c01v1Rx3LParam OBJECT-TYPE
			SYNTAX Uint16
			MAX-ACCESS read-only
			STATUS current
			DESCRIPTION
				"L parameter (FEC mode columns)"
		::= { ste2022c01v1Entry 451 }

		-- 1.3.6.1.4.1.10106.3.101291.1.1.453
		ste2022c01v1Rx3DParam OBJECT-TYPE
			SYNTAX Uint16
			MAX-ACCESS read-only
			STATUS current
			DESCRIPTION
				"D parameter (FEC mode rows)"
		::= { ste2022c01v1Entry 453 }

		-- 1.3.6.1.4.1.10106.3.101291.1.1.455
		ste2022c01v1Rx4FecMode OBJECT-TYPE
			SYNTAX FecModeSte
			MAX-ACCESS read-only
			STATUS current
			DESCRIPTION
				"Protocol"
		::= { ste2022c01v1Entry 455 }

		-- 1.3.6.1.4.1.10106.3.101291.1.1.457
		ste2022c01v1Rx4IpRxAdd3 OBJECT-TYPE
			SYNTAX Uint8
			MAX-ACCESS read-only
			STATUS current
			DESCRIPTION
				"RX packets source IP address (3)"
		::= { ste2022c01v1Entry 457 }

		-- 1.3.6.1.4.1.10106.3.101291.1.1.459
		ste2022c01v1Rx4IpRxAdd2 OBJECT-TYPE
			SYNTAX Uint8
			MAX-ACCESS read-only
			STATUS current
			DESCRIPTION
				"RX packets source IP address (2)"
		::= { ste2022c01v1Entry 459 }

		-- 1.3.6.1.4.1.10106.3.101291.1.1.461
		ste2022c01v1Rx4IpRxAdd1 OBJECT-TYPE
			SYNTAX Uint8
			MAX-ACCESS read-only
			STATUS current
			DESCRIPTION
				"RX packets source IP address (1)"
		::= { ste2022c01v1Entry 461 }

		-- 1.3.6.1.4.1.10106.3.101291.1.1.463
		ste2022c01v1Rx4IpRxAdd0 OBJECT-TYPE
			SYNTAX Uint8
			MAX-ACCESS read-only
			STATUS current
			DESCRIPTION
				"RX packets source IP address (0)"
		::= { ste2022c01v1Entry 463 }

		-- 1.3.6.1.4.1.10106.3.101291.1.1.465
		ste2022c01v1Rx4IpRxPort OBJECT-TYPE
			SYNTAX Uint16
			MAX-ACCESS read-only
			STATUS current
			DESCRIPTION
				"RX packets UDP source port"
		::= { ste2022c01v1Entry 465 }

		-- 1.3.6.1.4.1.10106.3.101291.1.1.467
		ste2022c01v1Rx4LParam OBJECT-TYPE
			SYNTAX Uint16
			MAX-ACCESS read-only
			STATUS current
			DESCRIPTION
				"L parameter (FEC mode columns)"
		::= { ste2022c01v1Entry 467 }

		-- 1.3.6.1.4.1.10106.3.101291.1.1.469
		ste2022c01v1Rx4DParam OBJECT-TYPE
			SYNTAX Uint16
			MAX-ACCESS read-only
			STATUS current
			DESCRIPTION
				"D parameter (FEC mode rows)"
		::= { ste2022c01v1Entry 469 }

		-- 1.3.6.1.4.1.10106.3.101291.1.1.471
		ste2022c01v1LocalIp2Add3 OBJECT-TYPE
			SYNTAX Uint8
			MAX-ACCESS read-write
			STATUS current
			DESCRIPTION
				"IP address (3)"
		::= { ste2022c01v1Entry 471 }

		-- 1.3.6.1.4.1.10106.3.101291.1.1.473
		ste2022c01v1LocalIp2Add2 OBJECT-TYPE
			SYNTAX Uint8
			MAX-ACCESS read-write
			STATUS current
			DESCRIPTION
				"IP address (2)"
		::= { ste2022c01v1Entry 473 }

		-- 1.3.6.1.4.1.10106.3.101291.1.1.475
		ste2022c01v1LocalIp2Add1 OBJECT-TYPE
			SYNTAX Uint8
			MAX-ACCESS read-write
			STATUS current
			DESCRIPTION
				"IP address (1)"
		::= { ste2022c01v1Entry 475 }

		-- 1.3.6.1.4.1.10106.3.101291.1.1.477
		ste2022c01v1LocalIp2Add0 OBJECT-TYPE
			SYNTAX Uint8
			MAX-ACCESS read-write
			STATUS current
			DESCRIPTION
				"IP address (0)"
		::= { ste2022c01v1Entry 477 }

		-- 1.3.6.1.4.1.10106.3.101291.1.1.479
		ste2022c01v1LocalIp2Msk3 OBJECT-TYPE
			SYNTAX Uint8
			MAX-ACCESS read-write
			STATUS current
			DESCRIPTION
				"IP mask (3)"
		::= { ste2022c01v1Entry 479 }

		-- 1.3.6.1.4.1.10106.3.101291.1.1.481
		ste2022c01v1LocalIp2Msk2 OBJECT-TYPE
			SYNTAX Uint8
			MAX-ACCESS read-write
			STATUS current
			DESCRIPTION
				"IP mask (2)"
		::= { ste2022c01v1Entry 481 }

		-- 1.3.6.1.4.1.10106.3.101291.1.1.483
		ste2022c01v1LocalIp2Msk1 OBJECT-TYPE
			SYNTAX Uint8
			MAX-ACCESS read-write
			STATUS current
			DESCRIPTION
				"IP mask (1)"
		::= { ste2022c01v1Entry 483 }

		-- 1.3.6.1.4.1.10106.3.101291.1.1.485
		ste2022c01v1LocalIp2Msk0 OBJECT-TYPE
			SYNTAX Uint8
			MAX-ACCESS read-write
			STATUS current
			DESCRIPTION
				"IP mask (0)"
		::= { ste2022c01v1Entry 485 }

		-- 1.3.6.1.4.1.10106.3.101291.1.1.487
		ste2022c01v1LocalIpGway3 OBJECT-TYPE
			SYNTAX Uint8
			MAX-ACCESS read-write
			STATUS current
			DESCRIPTION
				"Gateway IP address (3)"
		::= { ste2022c01v1Entry 487 }

		-- 1.3.6.1.4.1.10106.3.101291.1.1.489
		ste2022c01v1LocalIpGway2 OBJECT-TYPE
			SYNTAX Uint8
			MAX-ACCESS read-write
			STATUS current
			DESCRIPTION
				"Gateway IP address (2)"
		::= { ste2022c01v1Entry 489 }

		-- 1.3.6.1.4.1.10106.3.101291.1.1.491
		ste2022c01v1LocalIpGway1 OBJECT-TYPE
			SYNTAX Uint8
			MAX-ACCESS read-write
			STATUS current
			DESCRIPTION
				"Gateway IP address (1)"
		::= { ste2022c01v1Entry 491 }

		-- 1.3.6.1.4.1.10106.3.101291.1.1.493
		ste2022c01v1LocalIpGway0 OBJECT-TYPE
			SYNTAX Uint8
			MAX-ACCESS read-write
			STATUS current
			DESCRIPTION
				"Gateway IP address (0)"
		::= { ste2022c01v1Entry 493 }

		-- 1.3.6.1.4.1.10106.3.101291.1.1.495
		ste2022c01v1SysError OBJECT-TYPE
			SYNTAX SysError0
			MAX-ACCESS read-only
			STATUS current
			DESCRIPTION
				"System error. (Irrecoverable alarm or event)"
		::= { ste2022c01v1Entry 495 }

		-- 1.3.6.1.4.1.10106.3.101291.1.1.497
		ste2022c01v1NoSignal1 OBJECT-TYPE
			SYNTAX BitFail
			MAX-ACCESS read-only
			STATUS current
			DESCRIPTION
				"There is no SDI signal at the input or the format is not supported / SDI signal lock fail"
		::= { ste2022c01v1Entry 497 }

		-- 1.3.6.1.4.1.10106.3.101291.1.1.499
		ste2022c01v1NoSignal1Aux OBJECT-TYPE
			SYNTAX BitFail
			MAX-ACCESS read-only
			STATUS current
			DESCRIPTION
				"There is no SDI signal at the input or the format is not supported / SDI signal lock fail"
		::= { ste2022c01v1Entry 499 }

		-- 1.3.6.1.4.1.10106.3.101291.1.1.501
		ste2022c01v1EdhCrc1 OBJECT-TYPE
			SYNTAX BitFail
			MAX-ACCESS read-only
			STATUS current
			DESCRIPTION
				"There are EDH/CRC errors on SDI signal"
		::= { ste2022c01v1Entry 501 }

		-- 1.3.6.1.4.1.10106.3.101291.1.1.503
		ste2022c01v1Format1 OBJECT-TYPE
			SYNTAX SdiHd3gFmt3
			MAX-ACCESS read-only
			STATUS current
			DESCRIPTION
				"Indicates the SDI received signal format"
		::= { ste2022c01v1Entry 503 }

		-- 1.3.6.1.4.1.10106.3.101291.1.1.505
		ste2022c01v1Format1Aux OBJECT-TYPE
			SYNTAX SdiHd3gFmt3
			MAX-ACCESS read-only
			STATUS current
			DESCRIPTION
				"Indicates the SDI received signal format"
		::= { ste2022c01v1Entry 505 }

		-- 1.3.6.1.4.1.10106.3.101291.1.1.507
		ste2022c01v1NoSignal2 OBJECT-TYPE
			SYNTAX BitFail
			MAX-ACCESS read-only
			STATUS current
			DESCRIPTION
				"There is no SDI signal at the input or the format is not supported / SDI signal lock fail"
		::= { ste2022c01v1Entry 507 }

		-- 1.3.6.1.4.1.10106.3.101291.1.1.509
		ste2022c01v1EdhCrc2 OBJECT-TYPE
			SYNTAX BitFail
			MAX-ACCESS read-only
			STATUS current
			DESCRIPTION
				"There are EDH/CRC errors on SDI signal"
		::= { ste2022c01v1Entry 509 }

		-- 1.3.6.1.4.1.10106.3.101291.1.1.511
		ste2022c01v1Format2 OBJECT-TYPE
			SYNTAX SdiHd3gFmt3
			MAX-ACCESS read-only
			STATUS current
			DESCRIPTION
				"Indicates the SDI received signal format"
		::= { ste2022c01v1Entry 511 }

		-- 1.3.6.1.4.1.10106.3.101291.1.1.513
		ste2022c01v1NoSignal3 OBJECT-TYPE
			SYNTAX BitFail
			MAX-ACCESS read-only
			STATUS current
			DESCRIPTION
				"There is no SDI signal at the input or the format is not supported / SDI signal lock fail"
		::= { ste2022c01v1Entry 513 }

		-- 1.3.6.1.4.1.10106.3.101291.1.1.515
		ste2022c01v1EdhCrc3 OBJECT-TYPE
			SYNTAX BitFail
			MAX-ACCESS read-only
			STATUS current
			DESCRIPTION
				"There are EDH/CRC errors on SDI signal"
		::= { ste2022c01v1Entry 515 }

		-- 1.3.6.1.4.1.10106.3.101291.1.1.517
		ste2022c01v1Format3 OBJECT-TYPE
			SYNTAX SdiHd3gFmt3
			MAX-ACCESS read-only
			STATUS current
			DESCRIPTION
				"Indicates the SDI received signal format"
		::= { ste2022c01v1Entry 517 }

		-- 1.3.6.1.4.1.10106.3.101291.1.1.519
		ste2022c01v1NoSignal4 OBJECT-TYPE
			SYNTAX BitFail
			MAX-ACCESS read-only
			STATUS current
			DESCRIPTION
				"There is no SDI signal at the input or the format is not supported / SDI signal lock fail"
		::= { ste2022c01v1Entry 519 }

		-- 1.3.6.1.4.1.10106.3.101291.1.1.521
		ste2022c01v1EdhCrc4 OBJECT-TYPE
			SYNTAX BitFail
			MAX-ACCESS read-only
			STATUS current
			DESCRIPTION
				"There are EDH/CRC errors on SDI signal"
		::= { ste2022c01v1Entry 521 }

		-- 1.3.6.1.4.1.10106.3.101291.1.1.523
		ste2022c01v1Format4 OBJECT-TYPE
			SYNTAX SdiHd3gFmt3
			MAX-ACCESS read-only
			STATUS current
			DESCRIPTION
				"Indicates the SDI received signal format"
		::= { ste2022c01v1Entry 523 }

		-- 1.3.6.1.4.1.10106.3.101291.1.1.525
		ste2022c01v1FormatIp1 OBJECT-TYPE
			SYNTAX SdiHd3gFmt3
			MAX-ACCESS read-only
			STATUS current
			DESCRIPTION
				"Indicates the SDI received signal format through the ethernet interface"
		::= { ste2022c01v1Entry 525 }

		-- 1.3.6.1.4.1.10106.3.101291.1.1.527
		ste2022c01v1RxIpFail1 OBJECT-TYPE
			SYNTAX BitFail
			MAX-ACCESS read-only
			STATUS current
			DESCRIPTION
				"RX IP SDI signal valid"
		::= { ste2022c01v1Entry 527 }

		-- 1.3.6.1.4.1.10106.3.101291.1.1.529
		ste2022c01v1LostLine1 OBJECT-TYPE
			SYNTAX BitFail
			MAX-ACCESS read-only
			STATUS current
			DESCRIPTION
				"Line loss due to a loss of packets"
		::= { ste2022c01v1Entry 529 }

		-- 1.3.6.1.4.1.10106.3.101291.1.1.531
		ste2022c01v1FormatIp2 OBJECT-TYPE
			SYNTAX SdiHd3gFmt3
			MAX-ACCESS read-only
			STATUS current
			DESCRIPTION
				"Indicates the SDI received signal format through the ethernet interface"
		::= { ste2022c01v1Entry 531 }

		-- 1.3.6.1.4.1.10106.3.101291.1.1.533
		ste2022c01v1RxIpFail2 OBJECT-TYPE
			SYNTAX BitFail
			MAX-ACCESS read-only
			STATUS current
			DESCRIPTION
				"RX IP SDI signal valid"
		::= { ste2022c01v1Entry 533 }

		-- 1.3.6.1.4.1.10106.3.101291.1.1.535
		ste2022c01v1LostLine2 OBJECT-TYPE
			SYNTAX BitFail
			MAX-ACCESS read-only
			STATUS current
			DESCRIPTION
				"Line loss due to a loss of packets"
		::= { ste2022c01v1Entry 535 }

		-- 1.3.6.1.4.1.10106.3.101291.1.1.537
		ste2022c01v1FormatIp3 OBJECT-TYPE
			SYNTAX SdiHd3gFmt3
			MAX-ACCESS read-only
			STATUS current
			DESCRIPTION
				"Indicates the SDI received signal format through the ethernet interface"
		::= { ste2022c01v1Entry 537 }

		-- 1.3.6.1.4.1.10106.3.101291.1.1.539
		ste2022c01v1RxIpFail3 OBJECT-TYPE
			SYNTAX BitFail
			MAX-ACCESS read-only
			STATUS current
			DESCRIPTION
				"RX IP SDI signal valid"
		::= { ste2022c01v1Entry 539 }

		-- 1.3.6.1.4.1.10106.3.101291.1.1.541
		ste2022c01v1LostLine3 OBJECT-TYPE
			SYNTAX BitFail
			MAX-ACCESS read-only
			STATUS current
			DESCRIPTION
				"Line loss due to a loss of packets"
		::= { ste2022c01v1Entry 541 }

		-- 1.3.6.1.4.1.10106.3.101291.1.1.543
		ste2022c01v1FormatIp4 OBJECT-TYPE
			SYNTAX SdiHd3gFmt3
			MAX-ACCESS read-only
			STATUS current
			DESCRIPTION
				"Indicates the SDI received signal format through the ethernet interface"
		::= { ste2022c01v1Entry 543 }

		-- 1.3.6.1.4.1.10106.3.101291.1.1.545
		ste2022c01v1RxIpFail4 OBJECT-TYPE
			SYNTAX BitFail
			MAX-ACCESS read-only
			STATUS current
			DESCRIPTION
				"RX IP SDI signal valid"
		::= { ste2022c01v1Entry 545 }

		-- 1.3.6.1.4.1.10106.3.101291.1.1.547
		ste2022c01v1LostLine4 OBJECT-TYPE
			SYNTAX BitFail
			MAX-ACCESS read-only
			STATUS current
			DESCRIPTION
				"Line loss due to a loss of packets"
		::= { ste2022c01v1Entry 547 }

		-- 1.3.6.1.4.1.10106.3.101291.1.1.549
		ste2022c01v1Link OBJECT-TYPE
			SYNTAX EthStatus
			MAX-ACCESS read-only
			STATUS current
			DESCRIPTION
				"Ethernet conection status"
		::= { ste2022c01v1Entry 549 }

		-- 1.3.6.1.4.1.10106.3.101291.1.1.551
		ste2022c01v1EthRemoteFault OBJECT-TYPE
			SYNTAX BitFail
			MAX-ACCESS read-only
			STATUS current
			DESCRIPTION
				"Ethernet remote fault"
		::= { ste2022c01v1Entry 551 }

		-- 1.3.6.1.4.1.10106.3.101291.1.1.553
		ste2022c01v1EthTxActivity OBJECT-TYPE
			SYNTAX BitEthActivity
			MAX-ACCESS read-only
			STATUS current
			DESCRIPTION
				"TX activity"
		::= { ste2022c01v1Entry 553 }

		-- 1.3.6.1.4.1.10106.3.101291.1.1.555
		ste2022c01v1EthRxActivity OBJECT-TYPE
			SYNTAX BitEthActivity
			MAX-ACCESS read-only
			STATUS current
			DESCRIPTION
				"RX activity"
		::= { ste2022c01v1Entry 555 }

		-- 1.3.6.1.4.1.10106.3.101291.1.1.557
		ste2022c01v1ArpValid1 OBJECT-TYPE
			SYNTAX BitFailN
			MAX-ACCESS read-only
			STATUS current
			DESCRIPTION
				"Valid ARP response (Unicast mode)"
		::= { ste2022c01v1Entry 557 }

		-- 1.3.6.1.4.1.10106.3.101291.1.1.559
		ste2022c01v1IcmpError1 OBJECT-TYPE
			SYNTAX BitFail
			MAX-ACCESS read-only
			STATUS current
			DESCRIPTION
				"Destination unreachable (ICMP destination unrechable packets received)"
		::= { ste2022c01v1Entry 559 }

		-- 1.3.6.1.4.1.10106.3.101291.1.1.561
		ste2022c01v1ArpValid2 OBJECT-TYPE
			SYNTAX BitFailN
			MAX-ACCESS read-only
			STATUS current
			DESCRIPTION
				"Valid ARP response (Unicast mode)"
		::= { ste2022c01v1Entry 561 }

		-- 1.3.6.1.4.1.10106.3.101291.1.1.563
		ste2022c01v1IcmpError2 OBJECT-TYPE
			SYNTAX BitFail
			MAX-ACCESS read-only
			STATUS current
			DESCRIPTION
				"Destination unreachable (ICMP destination unrechable packets received)"
		::= { ste2022c01v1Entry 563 }

		-- 1.3.6.1.4.1.10106.3.101291.1.1.565
		ste2022c01v1ArpValid3 OBJECT-TYPE
			SYNTAX BitFailN
			MAX-ACCESS read-only
			STATUS current
			DESCRIPTION
				"Valid ARP response (Unicast mode)"
		::= { ste2022c01v1Entry 565 }

		-- 1.3.6.1.4.1.10106.3.101291.1.1.567
		ste2022c01v1IcmpError3 OBJECT-TYPE
			SYNTAX BitFail
			MAX-ACCESS read-only
			STATUS current
			DESCRIPTION
				"Destination unreachable (ICMP destination unrechable packets received)"
		::= { ste2022c01v1Entry 567 }

		-- 1.3.6.1.4.1.10106.3.101291.1.1.569
		ste2022c01v1ArpValid4 OBJECT-TYPE
			SYNTAX BitFailN
			MAX-ACCESS read-only
			STATUS current
			DESCRIPTION
				"Valid ARP response (Unicast mode)"
		::= { ste2022c01v1Entry 569 }

		-- 1.3.6.1.4.1.10106.3.101291.1.1.571
		ste2022c01v1IcmpError4 OBJECT-TYPE
			SYNTAX BitFail
			MAX-ACCESS read-only
			STATUS current
			DESCRIPTION
				"Destination unreachable (ICMP destination unrechable packets received)"
		::= { ste2022c01v1Entry 571 }

		-- 1.3.6.1.4.1.10106.3.101291.1.1.573
		ste2022c01v1RefLockFail OBJECT-TYPE
			SYNTAX BitFailN
			MAX-ACCESS read-only
			STATUS current
			DESCRIPTION
				"Indicates that the module is not locked to the reference"
		::= { ste2022c01v1Entry 573 }

		-- 1.3.6.1.4.1.10106.3.101291.1.1.575
		ste2022c01v1IntRefPres OBJECT-TYPE
			SYNTAX BitFail
			MAX-ACCESS read-only
			STATUS current
			DESCRIPTION
				"Indicates the internal reference presence"
		::= { ste2022c01v1Entry 575 }

		-- 1.3.6.1.4.1.10106.3.101291.1.1.577
		ste2022c01v1GlobalStatus OBJECT-TYPE
			SYNTAX BitFailN
			MAX-ACCESS read-only
			STATUS current
			DESCRIPTION
				"Global status"
		::= { ste2022c01v1Entry 577 }

		-- 1.3.6.1.4.1.10106.3.101291.1.1.579
		ste2022c01v1SpeedStatus OBJECT-TYPE
			SYNTAX BitFail
			MAX-ACCESS read-only
			STATUS current
			DESCRIPTION
				"Speed status.  Output bitrate over maximum range."
		::= { ste2022c01v1Entry 579 }

		-- 1.3.6.1.4.1.10106.3.101291.1.1.581
		ste2022c01v1Temperature OBJECT-TYPE
			SYNTAX TempKintex
			MAX-ACCESS read-only
			STATUS current
			DESCRIPTION
				"FPGA core temperature"
		::= { ste2022c01v1Entry 581 }

		-- 1.3.6.1.4.1.10106.3.101291.1.1.583
		ste2022c01v1SerialNo OBJECT-TYPE
			SYNTAX SerialNo
			MAX-ACCESS read-only
			STATUS current
			DESCRIPTION
				"Serial number"
		::= { ste2022c01v1Entry 583 }

		-- 1.3.6.1.4.1.10106.3.552801
		tly2010c01v1 OBJECT IDENTIFIER ::= { albalaProducts 552801 }

		-- 1.3.6.1.4.1.10106.3.552801.1
		tly2010c01v1Table  OBJECT-TYPE
			SYNTAX SEQUENCE OF Tly2010c01v1Entry
			MAX-ACCESS not-accessible
			STATUS current
			DESCRIPTION
				"Module  TLY2010C01V1 Table"
			::= { tly2010c01v1 1 }

		-- 1.3.6.1.4.1.10106.3.552801.1.1
		tly2010c01v1Entry  OBJECT-TYPE
			SYNTAX Tly2010c01v1Entry
			MAX-ACCESS not-accessible
			STATUS current
			DESCRIPTION
				"Module TLY2010C01V1 Entry"
			INDEX { tly2010c01v1Index }
			::= { tly2010c01v1Table 1 }

			Tly2010c01v1Entry ::=
			SEQUENCE {
				tly2010c01v1Index
				ModuleIndex,
				tly2010c01v1Gpo
				Gpos010,
				tly2010c01v1GpoTrapEnable
				AlarmEnable,
				tly2010c01v1VirtGpo
				Gpos0255,
				tly2010c01v1MasterBrdAdd
				ModuleSlot3,
				tly2010c01v1VirtMode
				VirtMode,
				tly2010c01v1PhyGpo
				Gpos010,
				tly2010c01v1PhyGpoTrapEnable
				AlarmEnable,
				tly2010c01v1SerialNo
				SerialNo
			 }

		-- 1.3.6.1.4.1.10106.3.101291.1.1.1
		tly2010c01v1Index OBJECT-TYPE
			SYNTAX ModuleIndex
			MAX-ACCESS read-only
			STATUS current
			DESCRIPTION
				"Index of TLY2010C01V1 Table"
		::= { tly2010c01v1Entry 1 }

		-- 1.3.6.1.4.1.10106.3.101291.1.1.3
		tly2010c01v1Gpo OBJECT-TYPE
			SYNTAX Gpos010
			MAX-ACCESS read-write
			STATUS current
			DESCRIPTION
				"Activated GPO"
		::= { tly2010c01v1Entry 3 }

		-- 1.3.6.1.4.1.10106.3.101291.1.1.4
		tly2010c01v1GpoTrapEnable OBJECT-TYPE
			SYNTAX AlarmEnable
			MAX-ACCESS read-write
			STATUS current
			DESCRIPTION
				"Activated GPO Trap Enable"
		::= { tly2010c01v1Entry 4 }

		-- 1.3.6.1.4.1.10106.3.101291.1.1.5
		tly2010c01v1VirtGpo OBJECT-TYPE
			SYNTAX Gpos0255
			MAX-ACCESS read-write
			STATUS current
			DESCRIPTION
				"Selected input"
		::= { tly2010c01v1Entry 5 }

		-- 1.3.6.1.4.1.10106.3.101291.1.1.7
		tly2010c01v1MasterBrdAdd OBJECT-TYPE
			SYNTAX ModuleSlot3
			MAX-ACCESS read-write
			STATUS current
			DESCRIPTION
				"Allows selecting the master module slot"
		::= { tly2010c01v1Entry 7 }

		-- 1.3.6.1.4.1.10106.3.101291.1.1.9
		tly2010c01v1VirtMode OBJECT-TYPE
			SYNTAX VirtMode
			MAX-ACCESS read-write
			STATUS current
			DESCRIPTION
				"Allows selecting the virtual GPO mode"
		::= { tly2010c01v1Entry 9 }

		-- 1.3.6.1.4.1.10106.3.101291.1.1.11
		tly2010c01v1PhyGpo OBJECT-TYPE
			SYNTAX Gpos010
			MAX-ACCESS read-only
			STATUS current
			DESCRIPTION
				"Indicates the active GPO"
		::= { tly2010c01v1Entry 11 }

		-- 1.3.6.1.4.1.10106.3.101291.1.1.12
		tly2010c01v1PhyGpoTrapEnable OBJECT-TYPE
			SYNTAX AlarmEnable
			MAX-ACCESS read-write
			STATUS current
			DESCRIPTION
				"Indicates the active GPO Trap Enable"
		::= { tly2010c01v1Entry 12 }

		-- 1.3.6.1.4.1.10106.3.101291.1.1.13
		tly2010c01v1SerialNo OBJECT-TYPE
			SYNTAX SerialNo
			MAX-ACCESS read-only
			STATUS current
			DESCRIPTION
				"Serial number"
		::= { tly2010c01v1Entry 13 }

		-- 1.3.6.1.4.1.10106.3.553101
		hli2000c01v1 OBJECT IDENTIFIER ::= { albalaProducts 553101 }

		-- 1.3.6.1.4.1.10106.3.553101.1
		hli2000c01v1Table  OBJECT-TYPE
			SYNTAX SEQUENCE OF Hli2000c01v1Entry
			MAX-ACCESS not-accessible
			STATUS current
			DESCRIPTION
				"Module  HLI2000C01V1 Table"
			::= { hli2000c01v1 1 }

		-- 1.3.6.1.4.1.10106.3.553101.1.1
		hli2000c01v1Entry  OBJECT-TYPE
			SYNTAX Hli2000c01v1Entry
			MAX-ACCESS not-accessible
			STATUS current
			DESCRIPTION
				"Module HLI2000C01V1 Entry"
			INDEX { hli2000c01v1Index }
			::= { hli2000c01v1Table 1 }

			Hli2000c01v1Entry ::=
			SEQUENCE {
				hli2000c01v1Index
				ModuleIndex,
				hli2000c01v1ActivePreset
				Preset16Active,
				hli2000c01v1LoadPreset
				Preset16Load,
				hli2000c01v1SavePreset
				Preset16Save,
				hli2000c01v1EnaAud20Bit
				Bit0No1Yes,
				hli2000c01v1IpAdd0
				Uint8,
				hli2000c01v1IpAdd1
				Uint8,
				hli2000c01v1IpAdd2
				Uint8,
				hli2000c01v1IpAdd3
				Uint8,
				hli2000c01v1IpMask0
				Uint8,
				hli2000c01v1IpMask1
				Uint8,
				hli2000c01v1IpMask2
				Uint8,
				hli2000c01v1IpMask3
				Uint8,
				hli2000c01v1IpGway0
				Uint8,
				hli2000c01v1IpGway1
				Uint8,
				hli2000c01v1IpGway2
				Uint8,
				hli2000c01v1IpGway3
				Uint8,
				hli2000c01v1LogoRdy1
				Bit0No1Yes,
				hli2000c01v1LogoRdy2
				Bit0No1Yes,
				hli2000c01v1AudioRdy
				Bit0No1Yes,
				hli2000c01v1FadeDur
				TimeX10Ms,
				hli2000c01v1FadeGain
				Att0dbInf,
				hli2000c01v1MixType
				Hli2MixType,
				hli2000c01v1LayerEn1
				Bit0No1Yes,
				hli2000c01v1LayerType1
				Hli2LayerType,
				hli2000c01v1FadeDur1
				DelayFram2,
				hli2000c01v1FadeTop1
				Rate1,
				hli2000c01v1CrawlEnLogo1
				Bit0No1Yes,
				hli2000c01v1CrawlPeriodic1
				Bit0No1Yes,
				hli2000c01v1CrawlSpeed1
				CrawlSpeed,
				hli2000c01v1CrawlTimeS1
				TimeS1,
				hli2000c01v1CrawlTimeM1
				TimeM1,
				hli2000c01v1CrawlTimeH1
				TimeH1,
				hli2000c01v1EnLogo11
				Bit0No1Yes,
				hli2000c01v1IdLogo11
				Uint8,
				hli2000c01v1XoffLogo11
				Int16,
				hli2000c01v1YoffLogo11
				Int16,
				hli2000c01v1EnLogo21
				Bit0No1Yes,
				hli2000c01v1IdLogo21
				Uint8,
				hli2000c01v1XoffLogo21
				Int16,
				hli2000c01v1YoffLogo21
				Int16,
				hli2000c01v1EnLogo31
				Bit0No1Yes,
				hli2000c01v1IdLogo31
				Uint8,
				hli2000c01v1XoffLogo31
				Int16,
				hli2000c01v1YoffLogo31
				Int16,
				hli2000c01v1EnLogo41
				Bit0No1Yes,
				hli2000c01v1IdLogo41
				Uint8,
				hli2000c01v1XoffLogo41
				Int16,
				hli2000c01v1YoffLogo41
				Int16,
				hli2000c01v1IdLogoAnim1
				Uint8,
				hli2000c01v1XoffLogoAnim1
				Int16,
				hli2000c01v1YoffLogoAnim1
				Int16,
				hli2000c01v1AniLogoType1
				Hli2AnimType,
				hli2000c01v1LayerEn2
				Bit0No1Yes,
				hli2000c01v1LayerType2
				Hli2LayerType,
				hli2000c01v1FadeDur2
				DelayFram2,
				hli2000c01v1FadeTop2
				Rate1,
				hli2000c01v1CrawlEnLogo2
				Bit0No1Yes,
				hli2000c01v1CrawlPeriodic2
				Bit0No1Yes,
				hli2000c01v1CrawlSpeed2
				CrawlSpeed,
				hli2000c01v1CrawlTimeS2
				TimeS1,
				hli2000c01v1CrawlTimeM2
				TimeM1,
				hli2000c01v1CrawlTimeH2
				TimeH1,
				hli2000c01v1EnLogo12
				Bit0No1Yes,
				hli2000c01v1IdLogo12
				Uint8,
				hli2000c01v1XoffLogo12
				Int16,
				hli2000c01v1YoffLogo12
				Int16,
				hli2000c01v1EnLogo22
				Bit0No1Yes,
				hli2000c01v1IdLogo22
				Uint8,
				hli2000c01v1XoffLogo22
				Int16,
				hli2000c01v1YoffLogo22
				Int16,
				hli2000c01v1EnLogo32
				Bit0No1Yes,
				hli2000c01v1IdLogo32
				Uint8,
				hli2000c01v1XoffLogo32
				Int16,
				hli2000c01v1YoffLogo32
				Int16,
				hli2000c01v1EnLogo42
				Bit0No1Yes,
				hli2000c01v1IdLogo42
				Uint8,
				hli2000c01v1XoffLogo42
				Int16,
				hli2000c01v1YoffLogo42
				Int16,
				hli2000c01v1IdLogoAnim2
				Uint8,
				hli2000c01v1XoffLogoAnim2
				Int16,
				hli2000c01v1YoffLogoAnim2
				Int16,
				hli2000c01v1AniLogoType2
				Hli2AnimType,
				hli2000c01v1IdLogoAud1
				Uint8,
				hli2000c01v1EnLogoAud1
				Bit0No1Yes,
				hli2000c01v1DstLogoAud1
				AudioMxIn5b,
				hli2000c01v1Loop1
				Bit0No1Yes,
				hli2000c01v1IdLogoAud2
				Uint8,
				hli2000c01v1EnLogoAud2
				Bit0No1Yes,
				hli2000c01v1DstLogoAud2
				AudioMxIn5b,
				hli2000c01v1Loop2
				Bit0No1Yes,
				hli2000c01v1IdLogoAud3
				Uint8,
				hli2000c01v1EnLogoAud3
				Bit0No1Yes,
				hli2000c01v1DstLogoAud3
				AudioMxIn5b,
				hli2000c01v1Loop3
				Bit0No1Yes,
				hli2000c01v1IdLogoAud4
				Uint8,
				hli2000c01v1EnLogoAud4
				Bit0No1Yes,
				hli2000c01v1DstLogoAud4
				AudioMxIn5b,
				hli2000c01v1Loop4
				Bit0No1Yes,
				hli2000c01v1SubsOutlEn1
				Bit0No1Yes,
				hli2000c01v1SubsOutlEn2
				Bit0No1Yes,
				hli2000c01v1HideVid1
				Bit0No1Yes,
				hli2000c01v1HideVid2
				Bit0No1Yes,
				hli2000c01v1SubsPage1
				Uint16,
				hli2000c01v1SubsPage2
				Uint16,
				hli2000c01v1SubsOpacity1
				Rate1,
				hli2000c01v1SubsOpacity2
				Rate1,
				hli2000c01v1SubsSizeOff1
				Size3,
				hli2000c01v1SubsSizeOff2
				Size3,
				hli2000c01v1TtxPage1
				Uint16,
				hli2000c01v1TtxPage2
				Uint16,
				hli2000c01v1RxFormat
				SdiHd3gFmt7,
				hli2000c01v1RxFormatTrapEnable
				AlarmEnable,
				hli2000c01v1VidValid
				BitFail,
				hli2000c01v1NoSignal
				BitFail,
				hli2000c01v1NoSignalTrapEnable
				AlarmEnable,
				hli2000c01v1EdhCrc
				BitFail,
				hli2000c01v1EdhCrcTrapEnable
				AlarmEnable,
				hli2000c01v1LockFail
				BitFail,
				hli2000c01v1LockFailTrapEnable
				AlarmEnable,
				hli2000c01v1Gpi1
				Bit0Clo1Open,
				hli2000c01v1Gpi2
				Bit0Clo1Open,
				hli2000c01v1FailTtx1
				BitFailN,
				hli2000c01v1FailTtx2
				BitFailN,
				hli2000c01v1Grp1Pres
				BitFailN,
				hli2000c01v1Grp2Pres
				BitFailN,
				hli2000c01v1Grp3Pres
				BitFailN,
				hli2000c01v1Grp4Pres
				BitFailN,
				hli2000c01v1EthLink
				Ipa2EtherStat,
				hli2000c01v1EthSystem
				Ipa2EtherSys,
				hli2000c01v1SerialNo
				SerialNo,
				hli2000c01v1ClockFormat
				ClockFormat,
				hli2000c01v1ClockAmPm
				ClockAmPm,
				hli2000c01v1ClockSize
				ClockSize,
				hli2000c01v1ClockEn
				BitMask,
				hli2000c01v1ClockPosition
				ClockPosition,
				hli2000c01v1TcSource
				TcSourceShort,
				hli2000c01v1AtcFail
				BitFail,
				hli2000c01v1DvitcFail
				BitFail,
				hli2000c01v1InputFPresSel
				Preset16Default
			 }

		-- 1.3.6.1.4.1.10106.3.101291.1.1.1
		hli2000c01v1Index OBJECT-TYPE
			SYNTAX ModuleIndex
			MAX-ACCESS read-only
			STATUS current
			DESCRIPTION
				"Index of HLI2000C01V1 Table"
		::= { hli2000c01v1Entry 1 }

		-- 1.3.6.1.4.1.10106.3.101291.1.1.3
		hli2000c01v1ActivePreset OBJECT-TYPE
			SYNTAX Preset16Active
			MAX-ACCESS read-only
			STATUS current
			DESCRIPTION
				"Shows the active preset"
		::= { hli2000c01v1Entry 3 }

		-- 1.3.6.1.4.1.10106.3.101291.1.1.5
		hli2000c01v1LoadPreset OBJECT-TYPE
			SYNTAX Preset16Load
			MAX-ACCESS read-write
			STATUS current
			DESCRIPTION
				"Allows loading a preset"
		::= { hli2000c01v1Entry 5 }

		-- 1.3.6.1.4.1.10106.3.101291.1.1.7
		hli2000c01v1SavePreset OBJECT-TYPE
			SYNTAX Preset16Save
			MAX-ACCESS read-write
			STATUS current
			DESCRIPTION
				"Allows saving a preset"
		::= { hli2000c01v1Entry 7 }

		-- 1.3.6.1.4.1.10106.3.101291.1.1.9
		hli2000c01v1EnaAud20Bit OBJECT-TYPE
			SYNTAX Bit0No1Yes
			MAX-ACCESS read-write
			STATUS current
			DESCRIPTION
				"Enable 20-bit audio instead of 24-bit"
		::= { hli2000c01v1Entry 9 }

		-- 1.3.6.1.4.1.10106.3.101291.1.1.11
		hli2000c01v1IpAdd0 OBJECT-TYPE
			SYNTAX Uint8
			MAX-ACCESS read-write
			STATUS current
			DESCRIPTION
				"Unicast IP address (0)"
		::= { hli2000c01v1Entry 11 }

		-- 1.3.6.1.4.1.10106.3.101291.1.1.13
		hli2000c01v1IpAdd1 OBJECT-TYPE
			SYNTAX Uint8
			MAX-ACCESS read-write
			STATUS current
			DESCRIPTION
				"Unicast IP address (1)"
		::= { hli2000c01v1Entry 13 }

		-- 1.3.6.1.4.1.10106.3.101291.1.1.15
		hli2000c01v1IpAdd2 OBJECT-TYPE
			SYNTAX Uint8
			MAX-ACCESS read-write
			STATUS current
			DESCRIPTION
				"Unicast IP address (2)"
		::= { hli2000c01v1Entry 15 }

		-- 1.3.6.1.4.1.10106.3.101291.1.1.17
		hli2000c01v1IpAdd3 OBJECT-TYPE
			SYNTAX Uint8
			MAX-ACCESS read-write
			STATUS current
			DESCRIPTION
				"Unicast IP address (3)"
		::= { hli2000c01v1Entry 17 }

		-- 1.3.6.1.4.1.10106.3.101291.1.1.19
		hli2000c01v1IpMask0 OBJECT-TYPE
			SYNTAX Uint8
			MAX-ACCESS read-write
			STATUS current
			DESCRIPTION
				"IP mask (0)"
		::= { hli2000c01v1Entry 19 }

		-- 1.3.6.1.4.1.10106.3.101291.1.1.21
		hli2000c01v1IpMask1 OBJECT-TYPE
			SYNTAX Uint8
			MAX-ACCESS read-write
			STATUS current
			DESCRIPTION
				"IP mask (1)"
		::= { hli2000c01v1Entry 21 }

		-- 1.3.6.1.4.1.10106.3.101291.1.1.23
		hli2000c01v1IpMask2 OBJECT-TYPE
			SYNTAX Uint8
			MAX-ACCESS read-write
			STATUS current
			DESCRIPTION
				"IP mask (2)"
		::= { hli2000c01v1Entry 23 }

		-- 1.3.6.1.4.1.10106.3.101291.1.1.25
		hli2000c01v1IpMask3 OBJECT-TYPE
			SYNTAX Uint8
			MAX-ACCESS read-write
			STATUS current
			DESCRIPTION
				"IP mask (3)"
		::= { hli2000c01v1Entry 25 }

		-- 1.3.6.1.4.1.10106.3.101291.1.1.27
		hli2000c01v1IpGway0 OBJECT-TYPE
			SYNTAX Uint8
			MAX-ACCESS read-write
			STATUS current
			DESCRIPTION
				"Gateway IP address (0)"
		::= { hli2000c01v1Entry 27 }

		-- 1.3.6.1.4.1.10106.3.101291.1.1.29
		hli2000c01v1IpGway1 OBJECT-TYPE
			SYNTAX Uint8
			MAX-ACCESS read-write
			STATUS current
			DESCRIPTION
				"Gateway IP address (1)"
		::= { hli2000c01v1Entry 29 }

		-- 1.3.6.1.4.1.10106.3.101291.1.1.31
		hli2000c01v1IpGway2 OBJECT-TYPE
			SYNTAX Uint8
			MAX-ACCESS read-write
			STATUS current
			DESCRIPTION
				"Gateway IP address (2)"
		::= { hli2000c01v1Entry 31 }

		-- 1.3.6.1.4.1.10106.3.101291.1.1.33
		hli2000c01v1IpGway3 OBJECT-TYPE
			SYNTAX Uint8
			MAX-ACCESS read-write
			STATUS current
			DESCRIPTION
				"Gateway IP address (3)"
		::= { hli2000c01v1Entry 33 }

		-- 1.3.6.1.4.1.10106.3.101291.1.1.35
		hli2000c01v1LogoRdy1 OBJECT-TYPE
			SYNTAX Bit0No1Yes
			MAX-ACCESS read-only
			STATUS current
			DESCRIPTION
				"Indicates that the layer is currently being rendered and cannot be shown"
		::= { hli2000c01v1Entry 35 }

		-- 1.3.6.1.4.1.10106.3.101291.1.1.37
		hli2000c01v1LogoRdy2 OBJECT-TYPE
			SYNTAX Bit0No1Yes
			MAX-ACCESS read-only
			STATUS current
			DESCRIPTION
				"Indicates that the layer is currently being rendered and cannot be shown"
		::= { hli2000c01v1Entry 37 }

		-- 1.3.6.1.4.1.10106.3.101291.1.1.39
		hli2000c01v1AudioRdy OBJECT-TYPE
			SYNTAX Bit0No1Yes
			MAX-ACCESS read-only
			STATUS current
			DESCRIPTION
				"Indicates that audio logos are currently being processed and cannot be played"
		::= { hli2000c01v1Entry 39 }

		-- 1.3.6.1.4.1.10106.3.101291.1.1.41
		hli2000c01v1FadeDur OBJECT-TYPE
			SYNTAX TimeX10Ms
			MAX-ACCESS read-write
			STATUS current
			DESCRIPTION
				"Input audio fade duration before and after audio logo plays"
		::= { hli2000c01v1Entry 41 }

		-- 1.3.6.1.4.1.10106.3.101291.1.1.43
		hli2000c01v1FadeGain OBJECT-TYPE
			SYNTAX Att0dbInf
			MAX-ACCESS read-write
			STATUS current
			DESCRIPTION
				"Attenuation applied to input audio at the end of the fade out"
		::= { hli2000c01v1Entry 43 }

		-- 1.3.6.1.4.1.10106.3.101291.1.1.45
		hli2000c01v1MixType OBJECT-TYPE
			SYNTAX Hli2MixType
			MAX-ACCESS read-write
			STATUS current
			DESCRIPTION
				"Selects technique for mixing the audio from the logo and the video input"
		::= { hli2000c01v1Entry 45 }

		-- 1.3.6.1.4.1.10106.3.101291.1.1.47
		hli2000c01v1LayerEn1 OBJECT-TYPE
			SYNTAX Bit0No1Yes
			MAX-ACCESS read-write
			STATUS current
			DESCRIPTION
				"Enable layer"
		::= { hli2000c01v1Entry 47 }

		-- 1.3.6.1.4.1.10106.3.101291.1.1.49
		hli2000c01v1LayerType1 OBJECT-TYPE
			SYNTAX Hli2LayerType
			MAX-ACCESS read-write
			STATUS current
			DESCRIPTION
				"Layer type"
		::= { hli2000c01v1Entry 49 }

		-- 1.3.6.1.4.1.10106.3.101291.1.1.51
		hli2000c01v1FadeDur1 OBJECT-TYPE
			SYNTAX DelayFram2
			MAX-ACCESS read-write
			STATUS current
			DESCRIPTION
				"Fade duration in frames (or fields when interlaced)"
		::= { hli2000c01v1Entry 51 }

		-- 1.3.6.1.4.1.10106.3.101291.1.1.53
		hli2000c01v1FadeTop1 OBJECT-TYPE
			SYNTAX Rate1
			MAX-ACCESS read-write
			STATUS current
			DESCRIPTION
				"Final fade opacity"
		::= { hli2000c01v1Entry 53 }

		-- 1.3.6.1.4.1.10106.3.101291.1.1.55
		hli2000c01v1CrawlEnLogo1 OBJECT-TYPE
			SYNTAX Bit0No1Yes
			MAX-ACCESS read-write
			STATUS current
			DESCRIPTION
				"Allows enabling crawl on logo"
		::= { hli2000c01v1Entry 55 }

		-- 1.3.6.1.4.1.10106.3.101291.1.1.57
		hli2000c01v1CrawlPeriodic1 OBJECT-TYPE
			SYNTAX Bit0No1Yes
			MAX-ACCESS read-write
			STATUS current
			DESCRIPTION
				"Enable periodic crawl"
		::= { hli2000c01v1Entry 57 }

		-- 1.3.6.1.4.1.10106.3.101291.1.1.59
		hli2000c01v1CrawlSpeed1 OBJECT-TYPE
			SYNTAX CrawlSpeed
			MAX-ACCESS read-write
			STATUS current
			DESCRIPTION
				"Allows adjusting the crawl speed"
		::= { hli2000c01v1Entry 59 }

		-- 1.3.6.1.4.1.10106.3.101291.1.1.61
		hli2000c01v1CrawlTimeS1 OBJECT-TYPE
			SYNTAX TimeS1
			MAX-ACCESS read-write
			STATUS current
			DESCRIPTION
				"Allows adjusting the crawl period (s)"
		::= { hli2000c01v1Entry 61 }

		-- 1.3.6.1.4.1.10106.3.101291.1.1.63
		hli2000c01v1CrawlTimeM1 OBJECT-TYPE
			SYNTAX TimeM1
			MAX-ACCESS read-write
			STATUS current
			DESCRIPTION
				"Allows adjusting the crawl period (m)"
		::= { hli2000c01v1Entry 63 }

		-- 1.3.6.1.4.1.10106.3.101291.1.1.65
		hli2000c01v1CrawlTimeH1 OBJECT-TYPE
			SYNTAX TimeH1
			MAX-ACCESS read-write
			STATUS current
			DESCRIPTION
				"Allows adjusting the crawl period (h)"
		::= { hli2000c01v1Entry 65 }

		-- 1.3.6.1.4.1.10106.3.101291.1.1.67
		hli2000c01v1EnLogo11 OBJECT-TYPE
			SYNTAX Bit0No1Yes
			MAX-ACCESS read-write
			STATUS current
			DESCRIPTION
				"Show logo 1"
		::= { hli2000c01v1Entry 67 }

		-- 1.3.6.1.4.1.10106.3.101291.1.1.69
		hli2000c01v1IdLogo11 OBJECT-TYPE
			SYNTAX Uint8
			MAX-ACCESS read-write
			STATUS current
			DESCRIPTION
				"Logo 1 ID"
		::= { hli2000c01v1Entry 69 }

		-- 1.3.6.1.4.1.10106.3.101291.1.1.71
		hli2000c01v1XoffLogo11 OBJECT-TYPE
			SYNTAX Int16
			MAX-ACCESS read-write
			STATUS current
			DESCRIPTION
				"Logo 1 X offset"
		::= { hli2000c01v1Entry 71 }

		-- 1.3.6.1.4.1.10106.3.101291.1.1.73
		hli2000c01v1YoffLogo11 OBJECT-TYPE
			SYNTAX Int16
			MAX-ACCESS read-write
			STATUS current
			DESCRIPTION
				"Logo 1 Y offset"
		::= { hli2000c01v1Entry 73 }

		-- 1.3.6.1.4.1.10106.3.101291.1.1.75
		hli2000c01v1EnLogo21 OBJECT-TYPE
			SYNTAX Bit0No1Yes
			MAX-ACCESS read-write
			STATUS current
			DESCRIPTION
				"Show logo 2"
		::= { hli2000c01v1Entry 75 }

		-- 1.3.6.1.4.1.10106.3.101291.1.1.77
		hli2000c01v1IdLogo21 OBJECT-TYPE
			SYNTAX Uint8
			MAX-ACCESS read-write
			STATUS current
			DESCRIPTION
				"Logo 2 ID"
		::= { hli2000c01v1Entry 77 }

		-- 1.3.6.1.4.1.10106.3.101291.1.1.79
		hli2000c01v1XoffLogo21 OBJECT-TYPE
			SYNTAX Int16
			MAX-ACCESS read-write
			STATUS current
			DESCRIPTION
				"Logo 2 X offset"
		::= { hli2000c01v1Entry 79 }

		-- 1.3.6.1.4.1.10106.3.101291.1.1.81
		hli2000c01v1YoffLogo21 OBJECT-TYPE
			SYNTAX Int16
			MAX-ACCESS read-write
			STATUS current
			DESCRIPTION
				"Logo 2 Y offset"
		::= { hli2000c01v1Entry 81 }

		-- 1.3.6.1.4.1.10106.3.101291.1.1.83
		hli2000c01v1EnLogo31 OBJECT-TYPE
			SYNTAX Bit0No1Yes
			MAX-ACCESS read-write
			STATUS current
			DESCRIPTION
				"Show logo 3"
		::= { hli2000c01v1Entry 83 }

		-- 1.3.6.1.4.1.10106.3.101291.1.1.85
		hli2000c01v1IdLogo31 OBJECT-TYPE
			SYNTAX Uint8
			MAX-ACCESS read-write
			STATUS current
			DESCRIPTION
				"Logo 3 ID"
		::= { hli2000c01v1Entry 85 }

		-- 1.3.6.1.4.1.10106.3.101291.1.1.87
		hli2000c01v1XoffLogo31 OBJECT-TYPE
			SYNTAX Int16
			MAX-ACCESS read-write
			STATUS current
			DESCRIPTION
				"Logo 3 X offset"
		::= { hli2000c01v1Entry 87 }

		-- 1.3.6.1.4.1.10106.3.101291.1.1.89
		hli2000c01v1YoffLogo31 OBJECT-TYPE
			SYNTAX Int16
			MAX-ACCESS read-write
			STATUS current
			DESCRIPTION
				"Logo 3 Y offset"
		::= { hli2000c01v1Entry 89 }

		-- 1.3.6.1.4.1.10106.3.101291.1.1.91
		hli2000c01v1EnLogo41 OBJECT-TYPE
			SYNTAX Bit0No1Yes
			MAX-ACCESS read-write
			STATUS current
			DESCRIPTION
				"Show logo 4"
		::= { hli2000c01v1Entry 91 }

		-- 1.3.6.1.4.1.10106.3.101291.1.1.93
		hli2000c01v1IdLogo41 OBJECT-TYPE
			SYNTAX Uint8
			MAX-ACCESS read-write
			STATUS current
			DESCRIPTION
				"Logo 4 ID"
		::= { hli2000c01v1Entry 93 }

		-- 1.3.6.1.4.1.10106.3.101291.1.1.95
		hli2000c01v1XoffLogo41 OBJECT-TYPE
			SYNTAX Int16
			MAX-ACCESS read-write
			STATUS current
			DESCRIPTION
				"Logo 4 X offset"
		::= { hli2000c01v1Entry 95 }

		-- 1.3.6.1.4.1.10106.3.101291.1.1.97
		hli2000c01v1YoffLogo41 OBJECT-TYPE
			SYNTAX Int16
			MAX-ACCESS read-write
			STATUS current
			DESCRIPTION
				"Logo 4 Y offset"
		::= { hli2000c01v1Entry 97 }

		-- 1.3.6.1.4.1.10106.3.101291.1.1.99
		hli2000c01v1IdLogoAnim1 OBJECT-TYPE
			SYNTAX Uint8
			MAX-ACCESS read-write
			STATUS current
			DESCRIPTION
				"Animated logo ID"
		::= { hli2000c01v1Entry 99 }

		-- 1.3.6.1.4.1.10106.3.101291.1.1.101
		hli2000c01v1XoffLogoAnim1 OBJECT-TYPE
			SYNTAX Int16
			MAX-ACCESS read-write
			STATUS current
			DESCRIPTION
				"Anim. logo X offset"
		::= { hli2000c01v1Entry 101 }

		-- 1.3.6.1.4.1.10106.3.101291.1.1.103
		hli2000c01v1YoffLogoAnim1 OBJECT-TYPE
			SYNTAX Int16
			MAX-ACCESS read-write
			STATUS current
			DESCRIPTION
				"Anim. logo Y offset"
		::= { hli2000c01v1Entry 103 }

		-- 1.3.6.1.4.1.10106.3.101291.1.1.105
		hli2000c01v1AniLogoType1 OBJECT-TYPE
			SYNTAX Hli2AnimType
			MAX-ACCESS read-only
			STATUS current
			DESCRIPTION
				"Animation type for selected logo"
		::= { hli2000c01v1Entry 105 }

		-- 1.3.6.1.4.1.10106.3.101291.1.1.107
		hli2000c01v1LayerEn2 OBJECT-TYPE
			SYNTAX Bit0No1Yes
			MAX-ACCESS read-write
			STATUS current
			DESCRIPTION
				"Enable layer"
		::= { hli2000c01v1Entry 107 }

		-- 1.3.6.1.4.1.10106.3.101291.1.1.109
		hli2000c01v1LayerType2 OBJECT-TYPE
			SYNTAX Hli2LayerType
			MAX-ACCESS read-write
			STATUS current
			DESCRIPTION
				"Layer type"
		::= { hli2000c01v1Entry 109 }

		-- 1.3.6.1.4.1.10106.3.101291.1.1.111
		hli2000c01v1FadeDur2 OBJECT-TYPE
			SYNTAX DelayFram2
			MAX-ACCESS read-write
			STATUS current
			DESCRIPTION
				"Fade duration in frames (or fields when interlaced)"
		::= { hli2000c01v1Entry 111 }

		-- 1.3.6.1.4.1.10106.3.101291.1.1.113
		hli2000c01v1FadeTop2 OBJECT-TYPE
			SYNTAX Rate1
			MAX-ACCESS read-write
			STATUS current
			DESCRIPTION
				"Final fade opacity"
		::= { hli2000c01v1Entry 113 }

		-- 1.3.6.1.4.1.10106.3.101291.1.1.115
		hli2000c01v1CrawlEnLogo2 OBJECT-TYPE
			SYNTAX Bit0No1Yes
			MAX-ACCESS read-write
			STATUS current
			DESCRIPTION
				"Allows enabling crawl on logo"
		::= { hli2000c01v1Entry 115 }

		-- 1.3.6.1.4.1.10106.3.101291.1.1.117
		hli2000c01v1CrawlPeriodic2 OBJECT-TYPE
			SYNTAX Bit0No1Yes
			MAX-ACCESS read-write
			STATUS current
			DESCRIPTION
				"Enable periodic crawl"
		::= { hli2000c01v1Entry 117 }

		-- 1.3.6.1.4.1.10106.3.101291.1.1.119
		hli2000c01v1CrawlSpeed2 OBJECT-TYPE
			SYNTAX CrawlSpeed
			MAX-ACCESS read-write
			STATUS current
			DESCRIPTION
				"Allows adjusting the crawl speed"
		::= { hli2000c01v1Entry 119 }

		-- 1.3.6.1.4.1.10106.3.101291.1.1.121
		hli2000c01v1CrawlTimeS2 OBJECT-TYPE
			SYNTAX TimeS1
			MAX-ACCESS read-write
			STATUS current
			DESCRIPTION
				"Allows adjusting the crawl period (s)"
		::= { hli2000c01v1Entry 121 }

		-- 1.3.6.1.4.1.10106.3.101291.1.1.123
		hli2000c01v1CrawlTimeM2 OBJECT-TYPE
			SYNTAX TimeM1
			MAX-ACCESS read-write
			STATUS current
			DESCRIPTION
				"Allows adjusting the crawl period (m)"
		::= { hli2000c01v1Entry 123 }

		-- 1.3.6.1.4.1.10106.3.101291.1.1.125
		hli2000c01v1CrawlTimeH2 OBJECT-TYPE
			SYNTAX TimeH1
			MAX-ACCESS read-write
			STATUS current
			DESCRIPTION
				"Allows adjusting the crawl period (h)"
		::= { hli2000c01v1Entry 125 }

		-- 1.3.6.1.4.1.10106.3.101291.1.1.127
		hli2000c01v1EnLogo12 OBJECT-TYPE
			SYNTAX Bit0No1Yes
			MAX-ACCESS read-write
			STATUS current
			DESCRIPTION
				"Show logo 1"
		::= { hli2000c01v1Entry 127 }

		-- 1.3.6.1.4.1.10106.3.101291.1.1.129
		hli2000c01v1IdLogo12 OBJECT-TYPE
			SYNTAX Uint8
			MAX-ACCESS read-write
			STATUS current
			DESCRIPTION
				"Logo 1 ID"
		::= { hli2000c01v1Entry 129 }

		-- 1.3.6.1.4.1.10106.3.101291.1.1.131
		hli2000c01v1XoffLogo12 OBJECT-TYPE
			SYNTAX Int16
			MAX-ACCESS read-write
			STATUS current
			DESCRIPTION
				"Logo 1 X offset"
		::= { hli2000c01v1Entry 131 }

		-- 1.3.6.1.4.1.10106.3.101291.1.1.133
		hli2000c01v1YoffLogo12 OBJECT-TYPE
			SYNTAX Int16
			MAX-ACCESS read-write
			STATUS current
			DESCRIPTION
				"Logo 1 Y offset"
		::= { hli2000c01v1Entry 133 }

		-- 1.3.6.1.4.1.10106.3.101291.1.1.135
		hli2000c01v1EnLogo22 OBJECT-TYPE
			SYNTAX Bit0No1Yes
			MAX-ACCESS read-write
			STATUS current
			DESCRIPTION
				"Show logo 2"
		::= { hli2000c01v1Entry 135 }

		-- 1.3.6.1.4.1.10106.3.101291.1.1.137
		hli2000c01v1IdLogo22 OBJECT-TYPE
			SYNTAX Uint8
			MAX-ACCESS read-write
			STATUS current
			DESCRIPTION
				"Logo 2 ID"
		::= { hli2000c01v1Entry 137 }

		-- 1.3.6.1.4.1.10106.3.101291.1.1.139
		hli2000c01v1XoffLogo22 OBJECT-TYPE
			SYNTAX Int16
			MAX-ACCESS read-write
			STATUS current
			DESCRIPTION
				"Logo 2 X offset"
		::= { hli2000c01v1Entry 139 }

		-- 1.3.6.1.4.1.10106.3.101291.1.1.141
		hli2000c01v1YoffLogo22 OBJECT-TYPE
			SYNTAX Int16
			MAX-ACCESS read-write
			STATUS current
			DESCRIPTION
				"Logo 2 Y offset"
		::= { hli2000c01v1Entry 141 }

		-- 1.3.6.1.4.1.10106.3.101291.1.1.143
		hli2000c01v1EnLogo32 OBJECT-TYPE
			SYNTAX Bit0No1Yes
			MAX-ACCESS read-write
			STATUS current
			DESCRIPTION
				"Show logo 3"
		::= { hli2000c01v1Entry 143 }

		-- 1.3.6.1.4.1.10106.3.101291.1.1.145
		hli2000c01v1IdLogo32 OBJECT-TYPE
			SYNTAX Uint8
			MAX-ACCESS read-write
			STATUS current
			DESCRIPTION
				"Logo 3 ID"
		::= { hli2000c01v1Entry 145 }

		-- 1.3.6.1.4.1.10106.3.101291.1.1.147
		hli2000c01v1XoffLogo32 OBJECT-TYPE
			SYNTAX Int16
			MAX-ACCESS read-write
			STATUS current
			DESCRIPTION
				"Logo 3 X offset"
		::= { hli2000c01v1Entry 147 }

		-- 1.3.6.1.4.1.10106.3.101291.1.1.149
		hli2000c01v1YoffLogo32 OBJECT-TYPE
			SYNTAX Int16
			MAX-ACCESS read-write
			STATUS current
			DESCRIPTION
				"Logo 3 Y offset"
		::= { hli2000c01v1Entry 149 }

		-- 1.3.6.1.4.1.10106.3.101291.1.1.151
		hli2000c01v1EnLogo42 OBJECT-TYPE
			SYNTAX Bit0No1Yes
			MAX-ACCESS read-write
			STATUS current
			DESCRIPTION
				"Show logo 4"
		::= { hli2000c01v1Entry 151 }

		-- 1.3.6.1.4.1.10106.3.101291.1.1.153
		hli2000c01v1IdLogo42 OBJECT-TYPE
			SYNTAX Uint8
			MAX-ACCESS read-write
			STATUS current
			DESCRIPTION
				"Logo 4 ID"
		::= { hli2000c01v1Entry 153 }

		-- 1.3.6.1.4.1.10106.3.101291.1.1.155
		hli2000c01v1XoffLogo42 OBJECT-TYPE
			SYNTAX Int16
			MAX-ACCESS read-write
			STATUS current
			DESCRIPTION
				"Logo 4 X offset"
		::= { hli2000c01v1Entry 155 }

		-- 1.3.6.1.4.1.10106.3.101291.1.1.157
		hli2000c01v1YoffLogo42 OBJECT-TYPE
			SYNTAX Int16
			MAX-ACCESS read-write
			STATUS current
			DESCRIPTION
				"Logo 4 Y offset"
		::= { hli2000c01v1Entry 157 }

		-- 1.3.6.1.4.1.10106.3.101291.1.1.159
		hli2000c01v1IdLogoAnim2 OBJECT-TYPE
			SYNTAX Uint8
			MAX-ACCESS read-write
			STATUS current
			DESCRIPTION
				"Animated logo ID"
		::= { hli2000c01v1Entry 159 }

		-- 1.3.6.1.4.1.10106.3.101291.1.1.161
		hli2000c01v1XoffLogoAnim2 OBJECT-TYPE
			SYNTAX Int16
			MAX-ACCESS read-write
			STATUS current
			DESCRIPTION
				"Anim. logo X offset"
		::= { hli2000c01v1Entry 161 }

		-- 1.3.6.1.4.1.10106.3.101291.1.1.163
		hli2000c01v1YoffLogoAnim2 OBJECT-TYPE
			SYNTAX Int16
			MAX-ACCESS read-write
			STATUS current
			DESCRIPTION
				"Anim. logo Y offset"
		::= { hli2000c01v1Entry 163 }

		-- 1.3.6.1.4.1.10106.3.101291.1.1.165
		hli2000c01v1AniLogoType2 OBJECT-TYPE
			SYNTAX Hli2AnimType
			MAX-ACCESS read-only
			STATUS current
			DESCRIPTION
				"Animation type for selected logo"
		::= { hli2000c01v1Entry 165 }

		-- 1.3.6.1.4.1.10106.3.101291.1.1.167
		hli2000c01v1IdLogoAud1 OBJECT-TYPE
			SYNTAX Uint8
			MAX-ACCESS read-write
			STATUS current
			DESCRIPTION
				"Audio logo 1 ID"
		::= { hli2000c01v1Entry 167 }

		-- 1.3.6.1.4.1.10106.3.101291.1.1.169
		hli2000c01v1EnLogoAud1 OBJECT-TYPE
			SYNTAX Bit0No1Yes
			MAX-ACCESS read-write
			STATUS current
			DESCRIPTION
				"Start playing audio logo 1"
		::= { hli2000c01v1Entry 169 }

		-- 1.3.6.1.4.1.10106.3.101291.1.1.171
		hli2000c01v1DstLogoAud1 OBJECT-TYPE
			SYNTAX AudioMxIn5b
			MAX-ACCESS read-write
			STATUS current
			DESCRIPTION
				"Audio logo 1 insertion pair"
		::= { hli2000c01v1Entry 171 }

		-- 1.3.6.1.4.1.10106.3.101291.1.1.173
		hli2000c01v1Loop1 OBJECT-TYPE
			SYNTAX Bit0No1Yes
			MAX-ACCESS read-write
			STATUS current
			DESCRIPTION
				"Loop logo 1"
		::= { hli2000c01v1Entry 173 }

		-- 1.3.6.1.4.1.10106.3.101291.1.1.175
		hli2000c01v1IdLogoAud2 OBJECT-TYPE
			SYNTAX Uint8
			MAX-ACCESS read-write
			STATUS current
			DESCRIPTION
				"Audio logo 2 ID"
		::= { hli2000c01v1Entry 175 }

		-- 1.3.6.1.4.1.10106.3.101291.1.1.177
		hli2000c01v1EnLogoAud2 OBJECT-TYPE
			SYNTAX Bit0No1Yes
			MAX-ACCESS read-write
			STATUS current
			DESCRIPTION
				"Start playing audio logo 2"
		::= { hli2000c01v1Entry 177 }

		-- 1.3.6.1.4.1.10106.3.101291.1.1.179
		hli2000c01v1DstLogoAud2 OBJECT-TYPE
			SYNTAX AudioMxIn5b
			MAX-ACCESS read-write
			STATUS current
			DESCRIPTION
				"Audio logo 2 insertion pair"
		::= { hli2000c01v1Entry 179 }

		-- 1.3.6.1.4.1.10106.3.101291.1.1.181
		hli2000c01v1Loop2 OBJECT-TYPE
			SYNTAX Bit0No1Yes
			MAX-ACCESS read-write
			STATUS current
			DESCRIPTION
				"Loop logo 2"
		::= { hli2000c01v1Entry 181 }

		-- 1.3.6.1.4.1.10106.3.101291.1.1.183
		hli2000c01v1IdLogoAud3 OBJECT-TYPE
			SYNTAX Uint8
			MAX-ACCESS read-write
			STATUS current
			DESCRIPTION
				"Audio logo 3 ID"
		::= { hli2000c01v1Entry 183 }

		-- 1.3.6.1.4.1.10106.3.101291.1.1.185
		hli2000c01v1EnLogoAud3 OBJECT-TYPE
			SYNTAX Bit0No1Yes
			MAX-ACCESS read-write
			STATUS current
			DESCRIPTION
				"Start playing audio logo 3"
		::= { hli2000c01v1Entry 185 }

		-- 1.3.6.1.4.1.10106.3.101291.1.1.187
		hli2000c01v1DstLogoAud3 OBJECT-TYPE
			SYNTAX AudioMxIn5b
			MAX-ACCESS read-write
			STATUS current
			DESCRIPTION
				"Audio logo 3 insertion pair"
		::= { hli2000c01v1Entry 187 }

		-- 1.3.6.1.4.1.10106.3.101291.1.1.189
		hli2000c01v1Loop3 OBJECT-TYPE
			SYNTAX Bit0No1Yes
			MAX-ACCESS read-write
			STATUS current
			DESCRIPTION
				"Loop logo 3"
		::= { hli2000c01v1Entry 189 }

		-- 1.3.6.1.4.1.10106.3.101291.1.1.191
		hli2000c01v1IdLogoAud4 OBJECT-TYPE
			SYNTAX Uint8
			MAX-ACCESS read-write
			STATUS current
			DESCRIPTION
				"Audio logo 4 ID"
		::= { hli2000c01v1Entry 191 }

		-- 1.3.6.1.4.1.10106.3.101291.1.1.193
		hli2000c01v1EnLogoAud4 OBJECT-TYPE
			SYNTAX Bit0No1Yes
			MAX-ACCESS read-write
			STATUS current
			DESCRIPTION
				"Start playing audio logo 4"
		::= { hli2000c01v1Entry 193 }

		-- 1.3.6.1.4.1.10106.3.101291.1.1.195
		hli2000c01v1DstLogoAud4 OBJECT-TYPE
			SYNTAX AudioMxIn5b
			MAX-ACCESS read-write
			STATUS current
			DESCRIPTION
				"Audio logo 4 insertion pair"
		::= { hli2000c01v1Entry 195 }

		-- 1.3.6.1.4.1.10106.3.101291.1.1.197
		hli2000c01v1Loop4 OBJECT-TYPE
			SYNTAX Bit0No1Yes
			MAX-ACCESS read-write
			STATUS current
			DESCRIPTION
				"Loop logo 4"
		::= { hli2000c01v1Entry 197 }

		-- 1.3.6.1.4.1.10106.3.101291.1.1.199
		hli2000c01v1SubsOutlEn1 OBJECT-TYPE
			SYNTAX Bit0No1Yes
			MAX-ACCESS read-write
			STATUS current
			DESCRIPTION
				"Enable caption outline"
		::= { hli2000c01v1Entry 199 }

		-- 1.3.6.1.4.1.10106.3.101291.1.1.201
		hli2000c01v1SubsOutlEn2 OBJECT-TYPE
			SYNTAX Bit0No1Yes
			MAX-ACCESS read-write
			STATUS current
			DESCRIPTION
				"Enable caption outline"
		::= { hli2000c01v1Entry 201 }

		-- 1.3.6.1.4.1.10106.3.101291.1.1.203
		hli2000c01v1HideVid1 OBJECT-TYPE
			SYNTAX Bit0No1Yes
			MAX-ACCESS read-write
			STATUS current
			DESCRIPTION
				"Hides input video while inserting teletext"
		::= { hli2000c01v1Entry 203 }

		-- 1.3.6.1.4.1.10106.3.101291.1.1.205
		hli2000c01v1HideVid2 OBJECT-TYPE
			SYNTAX Bit0No1Yes
			MAX-ACCESS read-write
			STATUS current
			DESCRIPTION
				"Hides input video while inserting teletext"
		::= { hli2000c01v1Entry 205 }

		-- 1.3.6.1.4.1.10106.3.101291.1.1.207
		hli2000c01v1SubsPage1 OBJECT-TYPE
			SYNTAX Uint16
			MAX-ACCESS read-write
			STATUS current
			DESCRIPTION
				"Subtitles page"
		::= { hli2000c01v1Entry 207 }

		-- 1.3.6.1.4.1.10106.3.101291.1.1.209
		hli2000c01v1SubsPage2 OBJECT-TYPE
			SYNTAX Uint16
			MAX-ACCESS read-write
			STATUS current
			DESCRIPTION
				"Subtitles page"
		::= { hli2000c01v1Entry 209 }

		-- 1.3.6.1.4.1.10106.3.101291.1.1.211
		hli2000c01v1SubsOpacity1 OBJECT-TYPE
			SYNTAX Rate1
			MAX-ACCESS read-write
			STATUS current
			DESCRIPTION
				"Caption background opacity"
		::= { hli2000c01v1Entry 211 }

		-- 1.3.6.1.4.1.10106.3.101291.1.1.213
		hli2000c01v1SubsOpacity2 OBJECT-TYPE
			SYNTAX Rate1
			MAX-ACCESS read-write
			STATUS current
			DESCRIPTION
				"Caption background opacity"
		::= { hli2000c01v1Entry 213 }

		-- 1.3.6.1.4.1.10106.3.101291.1.1.215
		hli2000c01v1SubsSizeOff1 OBJECT-TYPE
			SYNTAX Size3
			MAX-ACCESS read-write
			STATUS current
			DESCRIPTION
				"Caption size adjustment"
		::= { hli2000c01v1Entry 215 }

		-- 1.3.6.1.4.1.10106.3.101291.1.1.217
		hli2000c01v1SubsSizeOff2 OBJECT-TYPE
			SYNTAX Size3
			MAX-ACCESS read-write
			STATUS current
			DESCRIPTION
				"Caption size adjustment"
		::= { hli2000c01v1Entry 217 }

		-- 1.3.6.1.4.1.10106.3.101291.1.1.219
		hli2000c01v1TtxPage1 OBJECT-TYPE
			SYNTAX Uint16
			MAX-ACCESS read-write
			STATUS current
			DESCRIPTION
				"Teletext page"
		::= { hli2000c01v1Entry 219 }

		-- 1.3.6.1.4.1.10106.3.101291.1.1.221
		hli2000c01v1TtxPage2 OBJECT-TYPE
			SYNTAX Uint16
			MAX-ACCESS read-write
			STATUS current
			DESCRIPTION
				"Teletext page"
		::= { hli2000c01v1Entry 221 }

		-- 1.3.6.1.4.1.10106.3.101291.1.1.223
		hli2000c01v1RxFormat OBJECT-TYPE
			SYNTAX SdiHd3gFmt7
			MAX-ACCESS read-only
			STATUS current
			DESCRIPTION
				"Indicates the SDI received signal format"
		::= { hli2000c01v1Entry 223 }

		-- 1.3.6.1.4.1.10106.3.101291.1.1.224
		hli2000c01v1RxFormatTrapEnable OBJECT-TYPE
			SYNTAX AlarmEnable
			MAX-ACCESS read-write
			STATUS current
			DESCRIPTION
				"Indicates the SDI received signal format Trap Enable"
		::= { hli2000c01v1Entry 224 }

		-- 1.3.6.1.4.1.10106.3.101291.1.1.225
		hli2000c01v1VidValid OBJECT-TYPE
			SYNTAX BitFail
			MAX-ACCESS read-only
			STATUS current
			DESCRIPTION
				"SDI signal fail"
		::= { hli2000c01v1Entry 225 }

		-- 1.3.6.1.4.1.10106.3.101291.1.1.227
		hli2000c01v1NoSignal OBJECT-TYPE
			SYNTAX BitFail
			MAX-ACCESS read-only
			STATUS current
			DESCRIPTION
				"There is no SDI signal or the format is not supported"
		::= { hli2000c01v1Entry 227 }

		-- 1.3.6.1.4.1.10106.3.101291.1.1.228
		hli2000c01v1NoSignalTrapEnable OBJECT-TYPE
			SYNTAX AlarmEnable
			MAX-ACCESS read-write
			STATUS current
			DESCRIPTION
				"There is no SDI signal or the format is not supported Trap Enable"
		::= { hli2000c01v1Entry 228 }

		-- 1.3.6.1.4.1.10106.3.101291.1.1.229
		hli2000c01v1EdhCrc OBJECT-TYPE
			SYNTAX BitFail
			MAX-ACCESS read-only
			STATUS current
			DESCRIPTION
				"Indicates presence of EDH/CRC errors"
		::= { hli2000c01v1Entry 229 }

		-- 1.3.6.1.4.1.10106.3.101291.1.1.230
		hli2000c01v1EdhCrcTrapEnable OBJECT-TYPE
			SYNTAX AlarmEnable
			MAX-ACCESS read-write
			STATUS current
			DESCRIPTION
				"Indicates presence of EDH/CRC errors Trap Enable"
		::= { hli2000c01v1Entry 230 }

		-- 1.3.6.1.4.1.10106.3.101291.1.1.231
		hli2000c01v1LockFail OBJECT-TYPE
			SYNTAX BitFail
			MAX-ACCESS read-only
			STATUS current
			DESCRIPTION
				"Output video is not locked to input"
		::= { hli2000c01v1Entry 231 }

		-- 1.3.6.1.4.1.10106.3.101291.1.1.232
		hli2000c01v1LockFailTrapEnable OBJECT-TYPE
			SYNTAX AlarmEnable
			MAX-ACCESS read-write
			STATUS current
			DESCRIPTION
				"Output video is not locked to input Trap Enable"
		::= { hli2000c01v1Entry 232 }

		-- 1.3.6.1.4.1.10106.3.101291.1.1.233
		hli2000c01v1Gpi1 OBJECT-TYPE
			SYNTAX Bit0Clo1Open
			MAX-ACCESS read-only
			STATUS current
			DESCRIPTION
				"Indicates GPI 1 State"
		::= { hli2000c01v1Entry 233 }

		-- 1.3.6.1.4.1.10106.3.101291.1.1.235
		hli2000c01v1Gpi2 OBJECT-TYPE
			SYNTAX Bit0Clo1Open
			MAX-ACCESS read-only
			STATUS current
			DESCRIPTION
				"Indicates GPI 2 State"
		::= { hli2000c01v1Entry 235 }

		-- 1.3.6.1.4.1.10106.3.101291.1.1.237
		hli2000c01v1FailTtx1 OBJECT-TYPE
			SYNTAX BitFailN
			MAX-ACCESS read-only
			STATUS current
			DESCRIPTION
				"Teletext data not present"
		::= { hli2000c01v1Entry 237 }

		-- 1.3.6.1.4.1.10106.3.101291.1.1.239
		hli2000c01v1FailTtx2 OBJECT-TYPE
			SYNTAX BitFailN
			MAX-ACCESS read-only
			STATUS current
			DESCRIPTION
				"Teletext data not present"
		::= { hli2000c01v1Entry 239 }

		-- 1.3.6.1.4.1.10106.3.101291.1.1.241
		hli2000c01v1Grp1Pres OBJECT-TYPE
			SYNTAX BitFailN
			MAX-ACCESS read-only
			STATUS current
			DESCRIPTION
				"Group 1 presence"
		::= { hli2000c01v1Entry 241 }

		-- 1.3.6.1.4.1.10106.3.101291.1.1.243
		hli2000c01v1Grp2Pres OBJECT-TYPE
			SYNTAX BitFailN
			MAX-ACCESS read-only
			STATUS current
			DESCRIPTION
				"Group 2 presence"
		::= { hli2000c01v1Entry 243 }

		-- 1.3.6.1.4.1.10106.3.101291.1.1.245
		hli2000c01v1Grp3Pres OBJECT-TYPE
			SYNTAX BitFailN
			MAX-ACCESS read-only
			STATUS current
			DESCRIPTION
				"Group 3 presence"
		::= { hli2000c01v1Entry 245 }

		-- 1.3.6.1.4.1.10106.3.101291.1.1.247
		hli2000c01v1Grp4Pres OBJECT-TYPE
			SYNTAX BitFailN
			MAX-ACCESS read-only
			STATUS current
			DESCRIPTION
				"Group 4 presence"
		::= { hli2000c01v1Entry 247 }

		-- 1.3.6.1.4.1.10106.3.101291.1.1.249
		hli2000c01v1EthLink OBJECT-TYPE
			SYNTAX Ipa2EtherStat
			MAX-ACCESS read-only
			STATUS current
			DESCRIPTION
				"Ethernet conection status"
		::= { hli2000c01v1Entry 249 }

		-- 1.3.6.1.4.1.10106.3.101291.1.1.251
		hli2000c01v1EthSystem OBJECT-TYPE
			SYNTAX Ipa2EtherSys
			MAX-ACCESS read-only
			STATUS current
			DESCRIPTION
				"Ethernet conection system"
		::= { hli2000c01v1Entry 251 }

		-- 1.3.6.1.4.1.10106.3.101291.1.1.253
		hli2000c01v1SerialNo OBJECT-TYPE
			SYNTAX SerialNo
			MAX-ACCESS read-only
			STATUS current
			DESCRIPTION
				"Serial number"
		::= { hli2000c01v1Entry 253 }

		-- 1.3.6.1.4.1.10106.3.101291.1.1.255
		hli2000c01v1ClockFormat OBJECT-TYPE
			SYNTAX ClockFormat
			MAX-ACCESS read-write
			STATUS current
			DESCRIPTION
				"It allows selectign the clock format"
		::= { hli2000c01v1Entry 255 }

		-- 1.3.6.1.4.1.10106.3.101291.1.1.257
		hli2000c01v1ClockAmPm OBJECT-TYPE
			SYNTAX ClockAmPm
			MAX-ACCESS read-write
			STATUS current
			DESCRIPTION
				"It allows selecting the clock mode"
		::= { hli2000c01v1Entry 257 }

		-- 1.3.6.1.4.1.10106.3.101291.1.1.259
		hli2000c01v1ClockSize OBJECT-TYPE
			SYNTAX ClockSize
			MAX-ACCESS read-write
			STATUS current
			DESCRIPTION
				"It allows selecting the clock size"
		::= { hli2000c01v1Entry 259 }

		-- 1.3.6.1.4.1.10106.3.101291.1.1.261
		hli2000c01v1ClockEn OBJECT-TYPE
			SYNTAX BitMask
			MAX-ACCESS read-write
			STATUS current
			DESCRIPTION
				"It allows enabling the OSD insertion"
		::= { hli2000c01v1Entry 261 }

		-- 1.3.6.1.4.1.10106.3.101291.1.1.263
		hli2000c01v1ClockPosition OBJECT-TYPE
			SYNTAX ClockPosition
			MAX-ACCESS read-write
			STATUS current
			DESCRIPTION
				"It allows selecting the clock position in screen"
		::= { hli2000c01v1Entry 263 }

		-- 1.3.6.1.4.1.10106.3.101291.1.1.265
		hli2000c01v1TcSource OBJECT-TYPE
			SYNTAX TcSourceShort
			MAX-ACCESS read-write
			STATUS current
			DESCRIPTION
				"Selects where to read timecode from"
		::= { hli2000c01v1Entry 265 }

		-- 1.3.6.1.4.1.10106.3.101291.1.1.267
		hli2000c01v1AtcFail OBJECT-TYPE
			SYNTAX BitFail
			MAX-ACCESS read-only
			STATUS current
			DESCRIPTION
				"Signals whether ATC timecode is found in the input video"
		::= { hli2000c01v1Entry 267 }

		-- 1.3.6.1.4.1.10106.3.101291.1.1.269
		hli2000c01v1DvitcFail OBJECT-TYPE
			SYNTAX BitFail
			MAX-ACCESS read-only
			STATUS current
			DESCRIPTION
				"Signals whether D-VITC timecode is found in the input video"
		::= { hli2000c01v1Entry 269 }

		-- 1.3.6.1.4.1.10106.3.101291.1.1.271
		hli2000c01v1InputFPresSel OBJECT-TYPE
			SYNTAX Preset16Default
			MAX-ACCESS read-write
			STATUS current
			DESCRIPTION
				"Preset loaded when input fails"
		::= { hli2000c01v1Entry 271 }

		-- 1.3.6.1.4.1.10106.3.553901
		vct2000c01v1 OBJECT IDENTIFIER ::= { albalaProducts 553901 }

		-- 1.3.6.1.4.1.10106.3.553901.1
		vct2000c01v1Table  OBJECT-TYPE
			SYNTAX SEQUENCE OF Vct2000c01v1Entry
			MAX-ACCESS not-accessible
			STATUS current
			DESCRIPTION
				"Module  VCT2000C01V1 Table"
			::= { vct2000c01v1 1 }

		-- 1.3.6.1.4.1.10106.3.553901.1.1
		vct2000c01v1Entry  OBJECT-TYPE
			SYNTAX Vct2000c01v1Entry
			MAX-ACCESS not-accessible
			STATUS current
			DESCRIPTION
				"Module VCT2000C01V1 Entry"
			INDEX { vct2000c01v1Index }
			::= { vct2000c01v1Table 1 }

			Vct2000c01v1Entry ::=
			SEQUENCE {
				vct2000c01v1Index
				ModuleIndex,
				vct2000c01v1Mode
				ChgOverMode1,
				vct2000c01v1ModeTrapEnable
				AlarmEnable,
				vct2000c01v1Buzzer
				BitMask,
				vct2000c01v1Input
				ChgOverInput2,
				vct2000c01v1InputTrapEnable
				AlarmEnable,
				vct2000c01v1InputChange
				Bit0No1Yes,
				vct2000c01v1ActTime
				TimeX10Ms2,
				vct2000c01v1RecTime
				TimeX10Ms2,
				vct2000c01v1InpMainFail
				BitFail,
				vct2000c01v1InpMainFailTrapEnable
				AlarmEnable,
				vct2000c01v1GpiMainFail
				BitFail,
				vct2000c01v1GpiMainFailTrapEnable
				AlarmEnable,
				vct2000c01v1InpResFail
				BitFail,
				vct2000c01v1InpResFailTrapEnable
				AlarmEnable,
				vct2000c01v1GpiResFail
				BitFail,
				vct2000c01v1GpiResFailTrapEnable
				AlarmEnable,
				vct2000c01v1Gpo1
				Bit0Open1Clo,
				vct2000c01v1Gpo2
				Bit0Open1Clo,
				vct2000c01v1SerialNo
				SerialNo
			 }

		-- 1.3.6.1.4.1.10106.3.101291.1.1.1
		vct2000c01v1Index OBJECT-TYPE
			SYNTAX ModuleIndex
			MAX-ACCESS read-only
			STATUS current
			DESCRIPTION
				"Index of VCT2000C01V1 Table"
		::= { vct2000c01v1Entry 1 }

		-- 1.3.6.1.4.1.10106.3.101291.1.1.3
		vct2000c01v1Mode OBJECT-TYPE
			SYNTAX ChgOverMode1
			MAX-ACCESS read-write
			STATUS current
			DESCRIPTION
				"Allows selecting the switching mode"
		::= { vct2000c01v1Entry 3 }

		-- 1.3.6.1.4.1.10106.3.101291.1.1.4
		vct2000c01v1ModeTrapEnable OBJECT-TYPE
			SYNTAX AlarmEnable
			MAX-ACCESS read-write
			STATUS current
			DESCRIPTION
				"Allows selecting the switching mode Trap Enable"
		::= { vct2000c01v1Entry 4 }

		-- 1.3.6.1.4.1.10106.3.101291.1.1.5
		vct2000c01v1Buzzer OBJECT-TYPE
			SYNTAX BitMask
			MAX-ACCESS read-write
			STATUS current
			DESCRIPTION
				"Allows buzzer operation"
		::= { vct2000c01v1Entry 5 }

		-- 1.3.6.1.4.1.10106.3.101291.1.1.7
		vct2000c01v1Input OBJECT-TYPE
			SYNTAX ChgOverInput2
			MAX-ACCESS read-write
			STATUS current
			DESCRIPTION
				"Selected input"
		::= { vct2000c01v1Entry 7 }

		-- 1.3.6.1.4.1.10106.3.101291.1.1.8
		vct2000c01v1InputTrapEnable OBJECT-TYPE
			SYNTAX AlarmEnable
			MAX-ACCESS read-write
			STATUS current
			DESCRIPTION
				"Selected input Trap Enable"
		::= { vct2000c01v1Entry 8 }

		-- 1.3.6.1.4.1.10106.3.101291.1.1.9
		vct2000c01v1InputChange OBJECT-TYPE
			SYNTAX Bit0No1Yes
			MAX-ACCESS read-write
			STATUS current
			DESCRIPTION
				"Signals a change in selected input"
		::= { vct2000c01v1Entry 9 }

		-- 1.3.6.1.4.1.10106.3.101291.1.1.11
		vct2000c01v1ActTime OBJECT-TYPE
			SYNTAX TimeX10Ms2
			MAX-ACCESS read-write
			STATUS current
			DESCRIPTION
				"Allows adjusting the time from the failure start until it is signaled"
		::= { vct2000c01v1Entry 11 }

		-- 1.3.6.1.4.1.10106.3.101291.1.1.13
		vct2000c01v1RecTime OBJECT-TYPE
			SYNTAX TimeX10Ms2
			MAX-ACCESS read-write
			STATUS current
			DESCRIPTION
				"Allows adjusting the time from the failure stop until it is signaled"
		::= { vct2000c01v1Entry 13 }

		-- 1.3.6.1.4.1.10106.3.101291.1.1.15
		vct2000c01v1InpMainFail OBJECT-TYPE
			SYNTAX BitFail
			MAX-ACCESS read-only
			STATUS current
			DESCRIPTION
				"Main input status"
		::= { vct2000c01v1Entry 15 }

		-- 1.3.6.1.4.1.10106.3.101291.1.1.16
		vct2000c01v1InpMainFailTrapEnable OBJECT-TYPE
			SYNTAX AlarmEnable
			MAX-ACCESS read-write
			STATUS current
			DESCRIPTION
				"Main input status Trap Enable"
		::= { vct2000c01v1Entry 16 }

		-- 1.3.6.1.4.1.10106.3.101291.1.1.17
		vct2000c01v1GpiMainFail OBJECT-TYPE
			SYNTAX BitFail
			MAX-ACCESS read-only
			STATUS current
			DESCRIPTION
				"GPI main input status"
		::= { vct2000c01v1Entry 17 }

		-- 1.3.6.1.4.1.10106.3.101291.1.1.18
		vct2000c01v1GpiMainFailTrapEnable OBJECT-TYPE
			SYNTAX AlarmEnable
			MAX-ACCESS read-write
			STATUS current
			DESCRIPTION
				"GPI main input status Trap Enable"
		::= { vct2000c01v1Entry 18 }

		-- 1.3.6.1.4.1.10106.3.101291.1.1.19
		vct2000c01v1InpResFail OBJECT-TYPE
			SYNTAX BitFail
			MAX-ACCESS read-only
			STATUS current
			DESCRIPTION
				"Reserve input status"
		::= { vct2000c01v1Entry 19 }

		-- 1.3.6.1.4.1.10106.3.101291.1.1.20
		vct2000c01v1InpResFailTrapEnable OBJECT-TYPE
			SYNTAX AlarmEnable
			MAX-ACCESS read-write
			STATUS current
			DESCRIPTION
				"Reserve input status Trap Enable"
		::= { vct2000c01v1Entry 20 }

		-- 1.3.6.1.4.1.10106.3.101291.1.1.21
		vct2000c01v1GpiResFail OBJECT-TYPE
			SYNTAX BitFail
			MAX-ACCESS read-only
			STATUS current
			DESCRIPTION
				"GPI main input status"
		::= { vct2000c01v1Entry 21 }

		-- 1.3.6.1.4.1.10106.3.101291.1.1.22
		vct2000c01v1GpiResFailTrapEnable OBJECT-TYPE
			SYNTAX AlarmEnable
			MAX-ACCESS read-write
			STATUS current
			DESCRIPTION
				"GPI main input status Trap Enable"
		::= { vct2000c01v1Entry 22 }

		-- 1.3.6.1.4.1.10106.3.101291.1.1.23
		vct2000c01v1Gpo1 OBJECT-TYPE
			SYNTAX Bit0Open1Clo
			MAX-ACCESS read-only
			STATUS current
			DESCRIPTION
				"GPO1 state"
		::= { vct2000c01v1Entry 23 }

		-- 1.3.6.1.4.1.10106.3.101291.1.1.25
		vct2000c01v1Gpo2 OBJECT-TYPE
			SYNTAX Bit0Open1Clo
			MAX-ACCESS read-only
			STATUS current
			DESCRIPTION
				"GPO2 state"
		::= { vct2000c01v1Entry 25 }

		-- 1.3.6.1.4.1.10106.3.101291.1.1.27
		vct2000c01v1SerialNo OBJECT-TYPE
			SYNTAX SerialNo
			MAX-ACCESS read-only
			STATUS current
			DESCRIPTION
				"Serial number"
		::= { vct2000c01v1Entry 27 }

		-- 1.3.6.1.4.1.10106.3.554501
		hxc2000c01v1 OBJECT IDENTIFIER ::= { albalaProducts 554501 }

		-- 1.3.6.1.4.1.10106.3.554501.1
		hxc2000c01v1Table  OBJECT-TYPE
			SYNTAX SEQUENCE OF Hxc2000c01v1Entry
			MAX-ACCESS not-accessible
			STATUS current
			DESCRIPTION
				"Module  HXC2000C01V1 Table"
			::= { hxc2000c01v1 1 }

		-- 1.3.6.1.4.1.10106.3.554501.1.1
		hxc2000c01v1Entry  OBJECT-TYPE
			SYNTAX Hxc2000c01v1Entry
			MAX-ACCESS not-accessible
			STATUS current
			DESCRIPTION
				"Module HXC2000C01V1 Entry"
			INDEX { hxc2000c01v1Index }
			::= { hxc2000c01v1Table 1 }

			Hxc2000c01v1Entry ::=
			SEQUENCE {
				hxc2000c01v1Index
				ModuleIndex,
				hxc2000c01v1ActivePreset
				Preset16Active,
				hxc2000c01v1LoadPreset
				Preset16Load,
				hxc2000c01v1SavePreset
				Preset16Save,
				hxc2000c01v1AnaRefFmt
				SdiHd3gFmt6,
				hxc2000c01v1AnaRefFmtTrapEnable
				AlarmEnable,
				hxc2000c01v1GenlockMode
				GenlockM0de2,
				hxc2000c01v1EnaAud20Bit
				Bit0Yes1No,
				hxc2000c01v1FailMode
				Bit0Fre1Blk,
				hxc2000c01v1ModeConv
				Bit0Aut1Man,
				hxc2000c01v1ModeConvTrapEnable
				AlarmEnable,
				hxc2000c01v1OutAfd
				Afd1,
				hxc2000c01v1OutAfdTrapEnable
				AlarmEnable,
				hxc2000c01v1OutCf
				Cf1,
				hxc2000c01v1OutCfTrapEnable
				AlarmEnable,
				hxc2000c01v1Esc11
				BitMask,
				hxc2000c01v1InAfdExpct
				Afd1,
				hxc2000c01v1InAfdExpctTrapEnable
				AlarmEnable,
				hxc2000c01v1InCfExpct
				Cf1,
				hxc2000c01v1InCfExpctTrapEnable
				AlarmEnable,
				hxc2000c01v1TxFmt
				SdiHd3gFmt6,
				hxc2000c01v1TxFmtTrapEnable
				AlarmEnable,
				hxc2000c01v1DeintAlgorithm
				DeintAlgorithm,
				hxc2000c01v1DeintAlgorithmTrapEnable
				AlarmEnable,
				hxc2000c01v1OutEnaS2016
				Bit0No1Yes,
				hxc2000c01v1OutEnaVii
				Bit0No1Yes,
				hxc2000c01v1OutEnaWss
				Bit0No1Yes,
				hxc2000c01v1OutEnaVitc
				Bit0No1Yes,
				hxc2000c01v1OutEnaAtc
				Bit0No1Yes,
				hxc2000c01v1OutEnaTxt
				Bit0No1Yes,
				hxc2000c01v1OutEnaCea608
				Bit0No1Yes,
				hxc2000c01v1SelAudPair0
				AudioMxInput5,
				hxc2000c01v1SelAudPair1
				AudioMxInput5,
				hxc2000c01v1SelAudPair2
				AudioMxInput5,
				hxc2000c01v1SelAudPair3
				AudioMxInput5,
				hxc2000c01v1SelAudPair4
				AudioMxInput5,
				hxc2000c01v1SelAudPair5
				AudioMxInput5,
				hxc2000c01v1SelAudPair6
				AudioMxInput5,
				hxc2000c01v1SelAudPair7
				AudioMxInput5,
				hxc2000c01v1VDelay
				DelayLines2,
				hxc2000c01v1HDelay
				DelayPixel5,
				hxc2000c01v1Grp1P0Gain
				Gain24dbMute,
				hxc2000c01v1Grp1P0Phase
				Bit0Nor1Inv,
				hxc2000c01v1Grp1P1Gain
				Gain24dbMute,
				hxc2000c01v1Grp1P1Phase
				Bit0Nor1Inv,
				hxc2000c01v1Grp2P0Gain
				Gain24dbMute,
				hxc2000c01v1Grp2P0Phase
				Bit0Nor1Inv,
				hxc2000c01v1Grp2P1Gain
				Gain24dbMute,
				hxc2000c01v1Grp2P1Phase
				Bit0Nor1Inv,
				hxc2000c01v1Grp3P0Gain
				Gain24dbMute,
				hxc2000c01v1Grp3P0Phase
				Bit0Nor1Inv,
				hxc2000c01v1Grp3P1Gain
				Gain24dbMute,
				hxc2000c01v1Grp3P1Phase
				Bit0Nor1Inv,
				hxc2000c01v1Grp4P0Gain
				Gain24dbMute,
				hxc2000c01v1Grp4P0Phase
				Bit0Nor1Inv,
				hxc2000c01v1Grp4P1Gain
				Gain24dbMute,
				hxc2000c01v1Grp4P1Phase
				Bit0Nor1Inv,
				hxc2000c01v1StatFlash
				BitFailN,
				hxc2000c01v1InPhyFail
				BitFail,
				hxc2000c01v1InPhyFailTrapEnable
				AlarmEnable,
				hxc2000c01v1InFmtFail
				BitFail,
				hxc2000c01v1InFmtFailTrapEnable
				AlarmEnable,
				hxc2000c01v1InIncFail
				BitFail,
				hxc2000c01v1InIncFailTrapEnable
				AlarmEnable,
				hxc2000c01v1InPresCrcFail
				BitFail,
				hxc2000c01v1InCrcFail
				BitFail,
				hxc2000c01v1InCrcFailTrapEnable
				AlarmEnable,
				hxc2000c01v1InPrsS352Fail
				BitFail,
				hxc2000c01v1InS352Fail
				BitFail,
				hxc2000c01v1PresS2016Fail
				BitFail,
				hxc2000c01v1ErrS2016Fail
				BitFail,
				hxc2000c01v1PresAudG1Fail
				BitFail,
				hxc2000c01v1PresAudG1FailTrapEnable
				AlarmEnable,
				hxc2000c01v1PresAudG2Fail
				BitFail,
				hxc2000c01v1PresAudG2FailTrapEnable
				AlarmEnable,
				hxc2000c01v1PresAudG3Fail
				BitFail,
				hxc2000c01v1PresAudG3FailTrapEnable
				AlarmEnable,
				hxc2000c01v1PresAudG4Fail
				BitFail,
				hxc2000c01v1PresAudG4FailTrapEnable
				AlarmEnable,
				hxc2000c01v1RefFail
				BitFail,
				hxc2000c01v1RefFailTrapEnable
				AlarmEnable,
				hxc2000c01v1RefFmtFail
				BitFail,
				hxc2000c01v1RefFmtFailTrapEnable
				AlarmEnable,
				hxc2000c01v1LockFail
				BitFail,
				hxc2000c01v1LockFailTrapEnable
				AlarmEnable,
				hxc2000c01v1AudPair0Fail
				BitFail,
				hxc2000c01v1AudPair0FailTrapEnable
				AlarmEnable,
				hxc2000c01v1AudPair1Fail
				BitFail,
				hxc2000c01v1AudPair1FailTrapEnable
				AlarmEnable,
				hxc2000c01v1AudPair2Fail
				BitFail,
				hxc2000c01v1AudPair2FailTrapEnable
				AlarmEnable,
				hxc2000c01v1AudPair3Fail
				BitFail,
				hxc2000c01v1AudPair3FailTrapEnable
				AlarmEnable,
				hxc2000c01v1AudPair4Fail
				BitFail,
				hxc2000c01v1AudPair4FailTrapEnable
				AlarmEnable,
				hxc2000c01v1AudPair5Fail
				BitFail,
				hxc2000c01v1AudPair5FailTrapEnable
				AlarmEnable,
				hxc2000c01v1AudPair6Fail
				BitFail,
				hxc2000c01v1AudPair6FailTrapEnable
				AlarmEnable,
				hxc2000c01v1AudPair7Fail
				BitFail,
				hxc2000c01v1AudPair7FailTrapEnable
				AlarmEnable,
				hxc2000c01v1InAfdDetct
				Afd1,
				hxc2000c01v1InAfdDetctTrapEnable
				AlarmEnable,
				hxc2000c01v1InCfDetct
				Cf1,
				hxc2000c01v1InCfDetctTrapEnable
				AlarmEnable,
				hxc2000c01v1InFormat
				SdiHd3gFmt3,
				hxc2000c01v1InFormatTrapEnable
				AlarmEnable,
				hxc2000c01v1RefFormat
				SdiHd3gFmt3,
				hxc2000c01v1RefFormatTrapEnable
				AlarmEnable,
				hxc2000c01v1TxFormat
				SdiHd3gFmt3,
				hxc2000c01v1TxFormatTrapEnable
				AlarmEnable,
				hxc2000c01v1TxtPres
				BitFailN,
				hxc2000c01v1VitcPres
				BitFailN,
				hxc2000c01v1Mute
				Bit0No1Yes,
				hxc2000c01v1Black
				Bit0No1Yes,
				hxc2000c01v1Gpi1
				Bit0Off1On,
				hxc2000c01v1Gpi2
				Bit0Off1On,
				hxc2000c01v1Gpi3
				Bit0Off1On,
				hxc2000c01v1Gpi4
				Bit0Off1On,
				hxc2000c01v1SerialNo
				SerialNo,
				hxc2000c01v1MuteEna
				Bit0No1Yes
			 }

		-- 1.3.6.1.4.1.10106.3.101291.1.1.1
		hxc2000c01v1Index OBJECT-TYPE
			SYNTAX ModuleIndex
			MAX-ACCESS read-only
			STATUS current
			DESCRIPTION
				"Index of HXC2000C01V1 Table"
		::= { hxc2000c01v1Entry 1 }

		-- 1.3.6.1.4.1.10106.3.101291.1.1.3
		hxc2000c01v1ActivePreset OBJECT-TYPE
			SYNTAX Preset16Active
			MAX-ACCESS read-only
			STATUS current
			DESCRIPTION
				"Shows the active preset"
		::= { hxc2000c01v1Entry 3 }

		-- 1.3.6.1.4.1.10106.3.101291.1.1.5
		hxc2000c01v1LoadPreset OBJECT-TYPE
			SYNTAX Preset16Load
			MAX-ACCESS read-write
			STATUS current
			DESCRIPTION
				"Allows loading a preset"
		::= { hxc2000c01v1Entry 5 }

		-- 1.3.6.1.4.1.10106.3.101291.1.1.7
		hxc2000c01v1SavePreset OBJECT-TYPE
			SYNTAX Preset16Save
			MAX-ACCESS read-write
			STATUS current
			DESCRIPTION
				"Allows saving a preset"
		::= { hxc2000c01v1Entry 7 }

		-- 1.3.6.1.4.1.10106.3.101291.1.1.9
		hxc2000c01v1AnaRefFmt OBJECT-TYPE
			SYNTAX SdiHd3gFmt6
			MAX-ACCESS read-write
			STATUS current
			DESCRIPTION
				"Analog reference input format"
		::= { hxc2000c01v1Entry 9 }

		-- 1.3.6.1.4.1.10106.3.101291.1.1.10
		hxc2000c01v1AnaRefFmtTrapEnable OBJECT-TYPE
			SYNTAX AlarmEnable
			MAX-ACCESS read-write
			STATUS current
			DESCRIPTION
				"Analog reference input format Trap Enable"
		::= { hxc2000c01v1Entry 10 }

		-- 1.3.6.1.4.1.10106.3.101291.1.1.11
		hxc2000c01v1GenlockMode OBJECT-TYPE
			SYNTAX GenlockM0de2
			MAX-ACCESS read-write
			STATUS current
			DESCRIPTION
				"Allos selecting the reference input signal"
		::= { hxc2000c01v1Entry 11 }

		-- 1.3.6.1.4.1.10106.3.101291.1.1.13
		hxc2000c01v1EnaAud20Bit OBJECT-TYPE
			SYNTAX Bit0Yes1No
			MAX-ACCESS read-write
			STATUS current
			DESCRIPTION
				"Allows embedding 24-bit audio in SD signals"
		::= { hxc2000c01v1Entry 13 }

		-- 1.3.6.1.4.1.10106.3.101291.1.1.15
		hxc2000c01v1FailMode OBJECT-TYPE
			SYNTAX Bit0Fre1Blk
			MAX-ACCESS read-write
			STATUS current
			DESCRIPTION
				"Allows selecting the output video signal if the input fails"
		::= { hxc2000c01v1Entry 15 }

		-- 1.3.6.1.4.1.10106.3.101291.1.1.17
		hxc2000c01v1ModeConv OBJECT-TYPE
			SYNTAX Bit0Aut1Man
			MAX-ACCESS read-write
			STATUS current
			DESCRIPTION
				"Conversion mode"
		::= { hxc2000c01v1Entry 17 }

		-- 1.3.6.1.4.1.10106.3.101291.1.1.18
		hxc2000c01v1ModeConvTrapEnable OBJECT-TYPE
			SYNTAX AlarmEnable
			MAX-ACCESS read-write
			STATUS current
			DESCRIPTION
				"Conversion mode Trap Enable"
		::= { hxc2000c01v1Entry 18 }

		-- 1.3.6.1.4.1.10106.3.101291.1.1.19
		hxc2000c01v1OutAfd OBJECT-TYPE
			SYNTAX Afd1
			MAX-ACCESS read-write
			STATUS current
			DESCRIPTION
				"Output active format description"
		::= { hxc2000c01v1Entry 19 }

		-- 1.3.6.1.4.1.10106.3.101291.1.1.20
		hxc2000c01v1OutAfdTrapEnable OBJECT-TYPE
			SYNTAX AlarmEnable
			MAX-ACCESS read-write
			STATUS current
			DESCRIPTION
				"Output active format description Trap Enable"
		::= { hxc2000c01v1Entry 20 }

		-- 1.3.6.1.4.1.10106.3.101291.1.1.21
		hxc2000c01v1OutCf OBJECT-TYPE
			SYNTAX Cf1
			MAX-ACCESS read-write
			STATUS current
			DESCRIPTION
				"Output coded frame"
		::= { hxc2000c01v1Entry 21 }

		-- 1.3.6.1.4.1.10106.3.101291.1.1.22
		hxc2000c01v1OutCfTrapEnable OBJECT-TYPE
			SYNTAX AlarmEnable
			MAX-ACCESS read-write
			STATUS current
			DESCRIPTION
				"Output coded frame Trap Enable"
		::= { hxc2000c01v1Entry 22 }

		-- 1.3.6.1.4.1.10106.3.101291.1.1.23
		hxc2000c01v1Esc11 OBJECT-TYPE
			SYNTAX BitMask
			MAX-ACCESS read-write
			STATUS current
			DESCRIPTION
				"Enables the 1 to 1 scaling rate"
		::= { hxc2000c01v1Entry 23 }

		-- 1.3.6.1.4.1.10106.3.101291.1.1.25
		hxc2000c01v1InAfdExpct OBJECT-TYPE
			SYNTAX Afd1
			MAX-ACCESS read-write
			STATUS current
			DESCRIPTION
				"Input expected active format description"
		::= { hxc2000c01v1Entry 25 }

		-- 1.3.6.1.4.1.10106.3.101291.1.1.26
		hxc2000c01v1InAfdExpctTrapEnable OBJECT-TYPE
			SYNTAX AlarmEnable
			MAX-ACCESS read-write
			STATUS current
			DESCRIPTION
				"Input expected active format description Trap Enable"
		::= { hxc2000c01v1Entry 26 }

		-- 1.3.6.1.4.1.10106.3.101291.1.1.27
		hxc2000c01v1InCfExpct OBJECT-TYPE
			SYNTAX Cf1
			MAX-ACCESS read-write
			STATUS current
			DESCRIPTION
				"Input expected coded frame"
		::= { hxc2000c01v1Entry 27 }

		-- 1.3.6.1.4.1.10106.3.101291.1.1.28
		hxc2000c01v1InCfExpctTrapEnable OBJECT-TYPE
			SYNTAX AlarmEnable
			MAX-ACCESS read-write
			STATUS current
			DESCRIPTION
				"Input expected coded frame Trap Enable"
		::= { hxc2000c01v1Entry 28 }

		-- 1.3.6.1.4.1.10106.3.101291.1.1.29
		hxc2000c01v1TxFmt OBJECT-TYPE
			SYNTAX SdiHd3gFmt6
			MAX-ACCESS read-write
			STATUS current
			DESCRIPTION
				"Output format"
		::= { hxc2000c01v1Entry 29 }

		-- 1.3.6.1.4.1.10106.3.101291.1.1.30
		hxc2000c01v1TxFmtTrapEnable OBJECT-TYPE
			SYNTAX AlarmEnable
			MAX-ACCESS read-write
			STATUS current
			DESCRIPTION
				"Output format Trap Enable"
		::= { hxc2000c01v1Entry 30 }

		-- 1.3.6.1.4.1.10106.3.101291.1.1.31
		hxc2000c01v1DeintAlgorithm OBJECT-TYPE
			SYNTAX DeintAlgorithm
			MAX-ACCESS read-write
			STATUS current
			DESCRIPTION
				"Allows selecting the de-interlacing algorithm"
		::= { hxc2000c01v1Entry 31 }

		-- 1.3.6.1.4.1.10106.3.101291.1.1.32
		hxc2000c01v1DeintAlgorithmTrapEnable OBJECT-TYPE
			SYNTAX AlarmEnable
			MAX-ACCESS read-write
			STATUS current
			DESCRIPTION
				"Allows selecting the de-interlacing algorithm Trap Enable"
		::= { hxc2000c01v1Entry 32 }

		-- 1.3.6.1.4.1.10106.3.101291.1.1.33
		hxc2000c01v1OutEnaS2016 OBJECT-TYPE
			SYNTAX Bit0No1Yes
			MAX-ACCESS read-write
			STATUS current
			DESCRIPTION
				"Enables insertion of SMPTE 2016 packets in  OUT"
		::= { hxc2000c01v1Entry 33 }

		-- 1.3.6.1.4.1.10106.3.101291.1.1.35
		hxc2000c01v1OutEnaVii OBJECT-TYPE
			SYNTAX Bit0No1Yes
			MAX-ACCESS read-write
			STATUS current
			DESCRIPTION
				"Enables insertion of VII in OUT"
		::= { hxc2000c01v1Entry 35 }

		-- 1.3.6.1.4.1.10106.3.101291.1.1.37
		hxc2000c01v1OutEnaWss OBJECT-TYPE
			SYNTAX Bit0No1Yes
			MAX-ACCESS read-write
			STATUS current
			DESCRIPTION
				"Enables insertion of WSS in OUT"
		::= { hxc2000c01v1Entry 37 }

		-- 1.3.6.1.4.1.10106.3.101291.1.1.39
		hxc2000c01v1OutEnaVitc OBJECT-TYPE
			SYNTAX Bit0No1Yes
			MAX-ACCESS read-write
			STATUS current
			DESCRIPTION
				"Enables insertion of DVITC in OUT"
		::= { hxc2000c01v1Entry 39 }

		-- 1.3.6.1.4.1.10106.3.101291.1.1.41
		hxc2000c01v1OutEnaAtc OBJECT-TYPE
			SYNTAX Bit0No1Yes
			MAX-ACCESS read-write
			STATUS current
			DESCRIPTION
				"Enables insertion of ATC in OUT"
		::= { hxc2000c01v1Entry 41 }

		-- 1.3.6.1.4.1.10106.3.101291.1.1.43
		hxc2000c01v1OutEnaTxt OBJECT-TYPE
			SYNTAX Bit0No1Yes
			MAX-ACCESS read-write
			STATUS current
			DESCRIPTION
				"Enables insertion of TXT in OUT"
		::= { hxc2000c01v1Entry 43 }

		-- 1.3.6.1.4.1.10106.3.101291.1.1.45
		hxc2000c01v1OutEnaCea608 OBJECT-TYPE
			SYNTAX Bit0No1Yes
			MAX-ACCESS read-write
			STATUS current
			DESCRIPTION
				"Enables insertion of CEA608 modulation in OUT when format is 486I59.94 and CEA608 or CEA708 paquets are present"
		::= { hxc2000c01v1Entry 45 }

		-- 1.3.6.1.4.1.10106.3.101291.1.1.47
		hxc2000c01v1SelAudPair0 OBJECT-TYPE
			SYNTAX AudioMxInput5
			MAX-ACCESS read-write
			STATUS current
			DESCRIPTION
				"Selection of output audio for pair 0"
		::= { hxc2000c01v1Entry 47 }

		-- 1.3.6.1.4.1.10106.3.101291.1.1.49
		hxc2000c01v1SelAudPair1 OBJECT-TYPE
			SYNTAX AudioMxInput5
			MAX-ACCESS read-write
			STATUS current
			DESCRIPTION
				"Selection of output audio for pair 1"
		::= { hxc2000c01v1Entry 49 }

		-- 1.3.6.1.4.1.10106.3.101291.1.1.51
		hxc2000c01v1SelAudPair2 OBJECT-TYPE
			SYNTAX AudioMxInput5
			MAX-ACCESS read-write
			STATUS current
			DESCRIPTION
				"Selection of output audio for pair 2"
		::= { hxc2000c01v1Entry 51 }

		-- 1.3.6.1.4.1.10106.3.101291.1.1.53
		hxc2000c01v1SelAudPair3 OBJECT-TYPE
			SYNTAX AudioMxInput5
			MAX-ACCESS read-write
			STATUS current
			DESCRIPTION
				"Selection of output audio for pair 3"
		::= { hxc2000c01v1Entry 53 }

		-- 1.3.6.1.4.1.10106.3.101291.1.1.55
		hxc2000c01v1SelAudPair4 OBJECT-TYPE
			SYNTAX AudioMxInput5
			MAX-ACCESS read-write
			STATUS current
			DESCRIPTION
				"Selection of output audio for pair 4"
		::= { hxc2000c01v1Entry 55 }

		-- 1.3.6.1.4.1.10106.3.101291.1.1.57
		hxc2000c01v1SelAudPair5 OBJECT-TYPE
			SYNTAX AudioMxInput5
			MAX-ACCESS read-write
			STATUS current
			DESCRIPTION
				"Selection of output audio for pair 5"
		::= { hxc2000c01v1Entry 57 }

		-- 1.3.6.1.4.1.10106.3.101291.1.1.59
		hxc2000c01v1SelAudPair6 OBJECT-TYPE
			SYNTAX AudioMxInput5
			MAX-ACCESS read-write
			STATUS current
			DESCRIPTION
				"Selection of output audio for pair 6"
		::= { hxc2000c01v1Entry 59 }

		-- 1.3.6.1.4.1.10106.3.101291.1.1.61
		hxc2000c01v1SelAudPair7 OBJECT-TYPE
			SYNTAX AudioMxInput5
			MAX-ACCESS read-write
			STATUS current
			DESCRIPTION
				"Selection of output audio for pair 7"
		::= { hxc2000c01v1Entry 61 }

		-- 1.3.6.1.4.1.10106.3.101291.1.1.63
		hxc2000c01v1VDelay OBJECT-TYPE
			SYNTAX DelayLines2
			MAX-ACCESS read-write
			STATUS current
			DESCRIPTION
				"Allows adjusting the video vertical delay"
		::= { hxc2000c01v1Entry 63 }

		-- 1.3.6.1.4.1.10106.3.101291.1.1.65
		hxc2000c01v1HDelay OBJECT-TYPE
			SYNTAX DelayPixel5
			MAX-ACCESS read-write
			STATUS current
			DESCRIPTION
				"Allows adjusting the video horizontal delay"
		::= { hxc2000c01v1Entry 65 }

		-- 1.3.6.1.4.1.10106.3.101291.1.1.67
		hxc2000c01v1Grp1P0Gain OBJECT-TYPE
			SYNTAX Gain24dbMute
			MAX-ACCESS read-write
			STATUS current
			DESCRIPTION
				"Group 1 pair 0 gain"
		::= { hxc2000c01v1Entry 67 }

		-- 1.3.6.1.4.1.10106.3.101291.1.1.69
		hxc2000c01v1Grp1P0Phase OBJECT-TYPE
			SYNTAX Bit0Nor1Inv
			MAX-ACCESS read-write
			STATUS current
			DESCRIPTION
				"Group 1 pair 0 phase"
		::= { hxc2000c01v1Entry 69 }

		-- 1.3.6.1.4.1.10106.3.101291.1.1.71
		hxc2000c01v1Grp1P1Gain OBJECT-TYPE
			SYNTAX Gain24dbMute
			MAX-ACCESS read-write
			STATUS current
			DESCRIPTION
				"Group 1 pair 1 gain"
		::= { hxc2000c01v1Entry 71 }

		-- 1.3.6.1.4.1.10106.3.101291.1.1.73
		hxc2000c01v1Grp1P1Phase OBJECT-TYPE
			SYNTAX Bit0Nor1Inv
			MAX-ACCESS read-write
			STATUS current
			DESCRIPTION
				"Group 1 pair 1 phase"
		::= { hxc2000c01v1Entry 73 }

		-- 1.3.6.1.4.1.10106.3.101291.1.1.75
		hxc2000c01v1Grp2P0Gain OBJECT-TYPE
			SYNTAX Gain24dbMute
			MAX-ACCESS read-write
			STATUS current
			DESCRIPTION
				"Group 2 pair 0 gain"
		::= { hxc2000c01v1Entry 75 }

		-- 1.3.6.1.4.1.10106.3.101291.1.1.77
		hxc2000c01v1Grp2P0Phase OBJECT-TYPE
			SYNTAX Bit0Nor1Inv
			MAX-ACCESS read-write
			STATUS current
			DESCRIPTION
				"Group 2 pair 0 phase"
		::= { hxc2000c01v1Entry 77 }

		-- 1.3.6.1.4.1.10106.3.101291.1.1.79
		hxc2000c01v1Grp2P1Gain OBJECT-TYPE
			SYNTAX Gain24dbMute
			MAX-ACCESS read-write
			STATUS current
			DESCRIPTION
				"Group 2 pair 1 gain"
		::= { hxc2000c01v1Entry 79 }

		-- 1.3.6.1.4.1.10106.3.101291.1.1.81
		hxc2000c01v1Grp2P1Phase OBJECT-TYPE
			SYNTAX Bit0Nor1Inv
			MAX-ACCESS read-write
			STATUS current
			DESCRIPTION
				"Group 2 pair 1 phase"
		::= { hxc2000c01v1Entry 81 }

		-- 1.3.6.1.4.1.10106.3.101291.1.1.83
		hxc2000c01v1Grp3P0Gain OBJECT-TYPE
			SYNTAX Gain24dbMute
			MAX-ACCESS read-write
			STATUS current
			DESCRIPTION
				"Group 3 pair 0 gain"
		::= { hxc2000c01v1Entry 83 }

		-- 1.3.6.1.4.1.10106.3.101291.1.1.85
		hxc2000c01v1Grp3P0Phase OBJECT-TYPE
			SYNTAX Bit0Nor1Inv
			MAX-ACCESS read-write
			STATUS current
			DESCRIPTION
				"Group 3 pair 0 phase"
		::= { hxc2000c01v1Entry 85 }

		-- 1.3.6.1.4.1.10106.3.101291.1.1.87
		hxc2000c01v1Grp3P1Gain OBJECT-TYPE
			SYNTAX Gain24dbMute
			MAX-ACCESS read-write
			STATUS current
			DESCRIPTION
				"Group 3 pair 1 gain"
		::= { hxc2000c01v1Entry 87 }

		-- 1.3.6.1.4.1.10106.3.101291.1.1.89
		hxc2000c01v1Grp3P1Phase OBJECT-TYPE
			SYNTAX Bit0Nor1Inv
			MAX-ACCESS read-write
			STATUS current
			DESCRIPTION
				"Group 3 pair 1 phase"
		::= { hxc2000c01v1Entry 89 }

		-- 1.3.6.1.4.1.10106.3.101291.1.1.91
		hxc2000c01v1Grp4P0Gain OBJECT-TYPE
			SYNTAX Gain24dbMute
			MAX-ACCESS read-write
			STATUS current
			DESCRIPTION
				"Group 4 pair 0 gain"
		::= { hxc2000c01v1Entry 91 }

		-- 1.3.6.1.4.1.10106.3.101291.1.1.93
		hxc2000c01v1Grp4P0Phase OBJECT-TYPE
			SYNTAX Bit0Nor1Inv
			MAX-ACCESS read-write
			STATUS current
			DESCRIPTION
				"Group 4 pair 0 phase"
		::= { hxc2000c01v1Entry 93 }

		-- 1.3.6.1.4.1.10106.3.101291.1.1.95
		hxc2000c01v1Grp4P1Gain OBJECT-TYPE
			SYNTAX Gain24dbMute
			MAX-ACCESS read-write
			STATUS current
			DESCRIPTION
				"Group 4 pair 1 gain"
		::= { hxc2000c01v1Entry 95 }

		-- 1.3.6.1.4.1.10106.3.101291.1.1.97
		hxc2000c01v1Grp4P1Phase OBJECT-TYPE
			SYNTAX Bit0Nor1Inv
			MAX-ACCESS read-write
			STATUS current
			DESCRIPTION
				"Group 4 pair 1 phase"
		::= { hxc2000c01v1Entry 97 }

		-- 1.3.6.1.4.1.10106.3.101291.1.1.99
		hxc2000c01v1StatFlash OBJECT-TYPE
			SYNTAX BitFailN
			MAX-ACCESS read-only
			STATUS current
			DESCRIPTION
				"Displays the Flash state"
		::= { hxc2000c01v1Entry 99 }

		-- 1.3.6.1.4.1.10106.3.101291.1.1.101
		hxc2000c01v1InPhyFail OBJECT-TYPE
			SYNTAX BitFail
			MAX-ACCESS read-only
			STATUS current
			DESCRIPTION
				"Absence fail"
		::= { hxc2000c01v1Entry 101 }

		-- 1.3.6.1.4.1.10106.3.101291.1.1.102
		hxc2000c01v1InPhyFailTrapEnable OBJECT-TYPE
			SYNTAX AlarmEnable
			MAX-ACCESS read-write
			STATUS current
			DESCRIPTION
				"Absence fail Trap Enable"
		::= { hxc2000c01v1Entry 102 }

		-- 1.3.6.1.4.1.10106.3.101291.1.1.103
		hxc2000c01v1InFmtFail OBJECT-TYPE
			SYNTAX BitFail
			MAX-ACCESS read-only
			STATUS current
			DESCRIPTION
				"Format fail"
		::= { hxc2000c01v1Entry 103 }

		-- 1.3.6.1.4.1.10106.3.101291.1.1.104
		hxc2000c01v1InFmtFailTrapEnable OBJECT-TYPE
			SYNTAX AlarmEnable
			MAX-ACCESS read-write
			STATUS current
			DESCRIPTION
				"Format fail Trap Enable"
		::= { hxc2000c01v1Entry 104 }

		-- 1.3.6.1.4.1.10106.3.101291.1.1.105
		hxc2000c01v1InIncFail OBJECT-TYPE
			SYNTAX BitFail
			MAX-ACCESS read-only
			STATUS current
			DESCRIPTION
				"Incompatible format fail"
		::= { hxc2000c01v1Entry 105 }

		-- 1.3.6.1.4.1.10106.3.101291.1.1.106
		hxc2000c01v1InIncFailTrapEnable OBJECT-TYPE
			SYNTAX AlarmEnable
			MAX-ACCESS read-write
			STATUS current
			DESCRIPTION
				"Incompatible format fail Trap Enable"
		::= { hxc2000c01v1Entry 106 }

		-- 1.3.6.1.4.1.10106.3.101291.1.1.107
		hxc2000c01v1InPresCrcFail OBJECT-TYPE
			SYNTAX BitFail
			MAX-ACCESS read-only
			STATUS current
			DESCRIPTION
				"EDH/CRC presence fail"
		::= { hxc2000c01v1Entry 107 }

		-- 1.3.6.1.4.1.10106.3.101291.1.1.109
		hxc2000c01v1InCrcFail OBJECT-TYPE
			SYNTAX BitFail
			MAX-ACCESS read-only
			STATUS current
			DESCRIPTION
				"EDH/CRC fail"
		::= { hxc2000c01v1Entry 109 }

		-- 1.3.6.1.4.1.10106.3.101291.1.1.110
		hxc2000c01v1InCrcFailTrapEnable OBJECT-TYPE
			SYNTAX AlarmEnable
			MAX-ACCESS read-write
			STATUS current
			DESCRIPTION
				"EDH/CRC fail Trap Enable"
		::= { hxc2000c01v1Entry 110 }

		-- 1.3.6.1.4.1.10106.3.101291.1.1.111
		hxc2000c01v1InPrsS352Fail OBJECT-TYPE
			SYNTAX BitFail
			MAX-ACCESS read-only
			STATUS current
			DESCRIPTION
				"SMPTE 352 presence fail"
		::= { hxc2000c01v1Entry 111 }

		-- 1.3.6.1.4.1.10106.3.101291.1.1.113
		hxc2000c01v1InS352Fail OBJECT-TYPE
			SYNTAX BitFail
			MAX-ACCESS read-only
			STATUS current
			DESCRIPTION
				"SMPTE 352 fail"
		::= { hxc2000c01v1Entry 113 }

		-- 1.3.6.1.4.1.10106.3.101291.1.1.115
		hxc2000c01v1PresS2016Fail OBJECT-TYPE
			SYNTAX BitFail
			MAX-ACCESS read-only
			STATUS current
			DESCRIPTION
				"SMPTE 2016 presence fail"
		::= { hxc2000c01v1Entry 115 }

		-- 1.3.6.1.4.1.10106.3.101291.1.1.117
		hxc2000c01v1ErrS2016Fail OBJECT-TYPE
			SYNTAX BitFail
			MAX-ACCESS read-only
			STATUS current
			DESCRIPTION
				"SMPTE 2016 error fail"
		::= { hxc2000c01v1Entry 117 }

		-- 1.3.6.1.4.1.10106.3.101291.1.1.119
		hxc2000c01v1PresAudG1Fail OBJECT-TYPE
			SYNTAX BitFail
			MAX-ACCESS read-only
			STATUS current
			DESCRIPTION
				"Audio group 1 presence fail"
		::= { hxc2000c01v1Entry 119 }

		-- 1.3.6.1.4.1.10106.3.101291.1.1.120
		hxc2000c01v1PresAudG1FailTrapEnable OBJECT-TYPE
			SYNTAX AlarmEnable
			MAX-ACCESS read-write
			STATUS current
			DESCRIPTION
				"Audio group 1 presence fail Trap Enable"
		::= { hxc2000c01v1Entry 120 }

		-- 1.3.6.1.4.1.10106.3.101291.1.1.121
		hxc2000c01v1PresAudG2Fail OBJECT-TYPE
			SYNTAX BitFail
			MAX-ACCESS read-only
			STATUS current
			DESCRIPTION
				"Audio group 2 presence fail"
		::= { hxc2000c01v1Entry 121 }

		-- 1.3.6.1.4.1.10106.3.101291.1.1.122
		hxc2000c01v1PresAudG2FailTrapEnable OBJECT-TYPE
			SYNTAX AlarmEnable
			MAX-ACCESS read-write
			STATUS current
			DESCRIPTION
				"Audio group 2 presence fail Trap Enable"
		::= { hxc2000c01v1Entry 122 }

		-- 1.3.6.1.4.1.10106.3.101291.1.1.123
		hxc2000c01v1PresAudG3Fail OBJECT-TYPE
			SYNTAX BitFail
			MAX-ACCESS read-only
			STATUS current
			DESCRIPTION
				"Audio group 3 presence fail"
		::= { hxc2000c01v1Entry 123 }

		-- 1.3.6.1.4.1.10106.3.101291.1.1.124
		hxc2000c01v1PresAudG3FailTrapEnable OBJECT-TYPE
			SYNTAX AlarmEnable
			MAX-ACCESS read-write
			STATUS current
			DESCRIPTION
				"Audio group 3 presence fail Trap Enable"
		::= { hxc2000c01v1Entry 124 }

		-- 1.3.6.1.4.1.10106.3.101291.1.1.125
		hxc2000c01v1PresAudG4Fail OBJECT-TYPE
			SYNTAX BitFail
			MAX-ACCESS read-only
			STATUS current
			DESCRIPTION
				"Audio group 4 presence fail"
		::= { hxc2000c01v1Entry 125 }

		-- 1.3.6.1.4.1.10106.3.101291.1.1.126
		hxc2000c01v1PresAudG4FailTrapEnable OBJECT-TYPE
			SYNTAX AlarmEnable
			MAX-ACCESS read-write
			STATUS current
			DESCRIPTION
				"Audio group 4 presence fail Trap Enable"
		::= { hxc2000c01v1Entry 126 }

		-- 1.3.6.1.4.1.10106.3.101291.1.1.127
		hxc2000c01v1RefFail OBJECT-TYPE
			SYNTAX BitFail
			MAX-ACCESS read-only
			STATUS current
			DESCRIPTION
				"Analog reference absence fail"
		::= { hxc2000c01v1Entry 127 }

		-- 1.3.6.1.4.1.10106.3.101291.1.1.128
		hxc2000c01v1RefFailTrapEnable OBJECT-TYPE
			SYNTAX AlarmEnable
			MAX-ACCESS read-write
			STATUS current
			DESCRIPTION
				"Analog reference absence fail Trap Enable"
		::= { hxc2000c01v1Entry 128 }

		-- 1.3.6.1.4.1.10106.3.101291.1.1.129
		hxc2000c01v1RefFmtFail OBJECT-TYPE
			SYNTAX BitFail
			MAX-ACCESS read-only
			STATUS current
			DESCRIPTION
				"Analog reference format fail"
		::= { hxc2000c01v1Entry 129 }

		-- 1.3.6.1.4.1.10106.3.101291.1.1.130
		hxc2000c01v1RefFmtFailTrapEnable OBJECT-TYPE
			SYNTAX AlarmEnable
			MAX-ACCESS read-write
			STATUS current
			DESCRIPTION
				"Analog reference format fail Trap Enable"
		::= { hxc2000c01v1Entry 130 }

		-- 1.3.6.1.4.1.10106.3.101291.1.1.131
		hxc2000c01v1LockFail OBJECT-TYPE
			SYNTAX BitFail
			MAX-ACCESS read-only
			STATUS current
			DESCRIPTION
				"Reference unlock fail"
		::= { hxc2000c01v1Entry 131 }

		-- 1.3.6.1.4.1.10106.3.101291.1.1.132
		hxc2000c01v1LockFailTrapEnable OBJECT-TYPE
			SYNTAX AlarmEnable
			MAX-ACCESS read-write
			STATUS current
			DESCRIPTION
				"Reference unlock fail Trap Enable"
		::= { hxc2000c01v1Entry 132 }

		-- 1.3.6.1.4.1.10106.3.101291.1.1.133
		hxc2000c01v1AudPair0Fail OBJECT-TYPE
			SYNTAX BitFail
			MAX-ACCESS read-only
			STATUS current
			DESCRIPTION
				"Audio pair 0 fail"
		::= { hxc2000c01v1Entry 133 }

		-- 1.3.6.1.4.1.10106.3.101291.1.1.134
		hxc2000c01v1AudPair0FailTrapEnable OBJECT-TYPE
			SYNTAX AlarmEnable
			MAX-ACCESS read-write
			STATUS current
			DESCRIPTION
				"Audio pair 0 fail Trap Enable"
		::= { hxc2000c01v1Entry 134 }

		-- 1.3.6.1.4.1.10106.3.101291.1.1.135
		hxc2000c01v1AudPair1Fail OBJECT-TYPE
			SYNTAX BitFail
			MAX-ACCESS read-only
			STATUS current
			DESCRIPTION
				"Audio pair 1 fail"
		::= { hxc2000c01v1Entry 135 }

		-- 1.3.6.1.4.1.10106.3.101291.1.1.136
		hxc2000c01v1AudPair1FailTrapEnable OBJECT-TYPE
			SYNTAX AlarmEnable
			MAX-ACCESS read-write
			STATUS current
			DESCRIPTION
				"Audio pair 1 fail Trap Enable"
		::= { hxc2000c01v1Entry 136 }

		-- 1.3.6.1.4.1.10106.3.101291.1.1.137
		hxc2000c01v1AudPair2Fail OBJECT-TYPE
			SYNTAX BitFail
			MAX-ACCESS read-only
			STATUS current
			DESCRIPTION
				"Audio pair 2 fail"
		::= { hxc2000c01v1Entry 137 }

		-- 1.3.6.1.4.1.10106.3.101291.1.1.138
		hxc2000c01v1AudPair2FailTrapEnable OBJECT-TYPE
			SYNTAX AlarmEnable
			MAX-ACCESS read-write
			STATUS current
			DESCRIPTION
				"Audio pair 2 fail Trap Enable"
		::= { hxc2000c01v1Entry 138 }

		-- 1.3.6.1.4.1.10106.3.101291.1.1.139
		hxc2000c01v1AudPair3Fail OBJECT-TYPE
			SYNTAX BitFail
			MAX-ACCESS read-only
			STATUS current
			DESCRIPTION
				"Audio pair 3 fail"
		::= { hxc2000c01v1Entry 139 }

		-- 1.3.6.1.4.1.10106.3.101291.1.1.140
		hxc2000c01v1AudPair3FailTrapEnable OBJECT-TYPE
			SYNTAX AlarmEnable
			MAX-ACCESS read-write
			STATUS current
			DESCRIPTION
				"Audio pair 3 fail Trap Enable"
		::= { hxc2000c01v1Entry 140 }

		-- 1.3.6.1.4.1.10106.3.101291.1.1.141
		hxc2000c01v1AudPair4Fail OBJECT-TYPE
			SYNTAX BitFail
			MAX-ACCESS read-only
			STATUS current
			DESCRIPTION
				"Audio pair 4 fail"
		::= { hxc2000c01v1Entry 141 }

		-- 1.3.6.1.4.1.10106.3.101291.1.1.142
		hxc2000c01v1AudPair4FailTrapEnable OBJECT-TYPE
			SYNTAX AlarmEnable
			MAX-ACCESS read-write
			STATUS current
			DESCRIPTION
				"Audio pair 4 fail Trap Enable"
		::= { hxc2000c01v1Entry 142 }

		-- 1.3.6.1.4.1.10106.3.101291.1.1.143
		hxc2000c01v1AudPair5Fail OBJECT-TYPE
			SYNTAX BitFail
			MAX-ACCESS read-only
			STATUS current
			DESCRIPTION
				"Audio pair 5 fail"
		::= { hxc2000c01v1Entry 143 }

		-- 1.3.6.1.4.1.10106.3.101291.1.1.144
		hxc2000c01v1AudPair5FailTrapEnable OBJECT-TYPE
			SYNTAX AlarmEnable
			MAX-ACCESS read-write
			STATUS current
			DESCRIPTION
				"Audio pair 5 fail Trap Enable"
		::= { hxc2000c01v1Entry 144 }

		-- 1.3.6.1.4.1.10106.3.101291.1.1.145
		hxc2000c01v1AudPair6Fail OBJECT-TYPE
			SYNTAX BitFail
			MAX-ACCESS read-only
			STATUS current
			DESCRIPTION
				"Audio pair 6 fail"
		::= { hxc2000c01v1Entry 145 }

		-- 1.3.6.1.4.1.10106.3.101291.1.1.146
		hxc2000c01v1AudPair6FailTrapEnable OBJECT-TYPE
			SYNTAX AlarmEnable
			MAX-ACCESS read-write
			STATUS current
			DESCRIPTION
				"Audio pair 6 fail Trap Enable"
		::= { hxc2000c01v1Entry 146 }

		-- 1.3.6.1.4.1.10106.3.101291.1.1.147
		hxc2000c01v1AudPair7Fail OBJECT-TYPE
			SYNTAX BitFail
			MAX-ACCESS read-only
			STATUS current
			DESCRIPTION
				"Audio pair 7 fail"
		::= { hxc2000c01v1Entry 147 }

		-- 1.3.6.1.4.1.10106.3.101291.1.1.148
		hxc2000c01v1AudPair7FailTrapEnable OBJECT-TYPE
			SYNTAX AlarmEnable
			MAX-ACCESS read-write
			STATUS current
			DESCRIPTION
				"Audio pair 7 fail Trap Enable"
		::= { hxc2000c01v1Entry 148 }

		-- 1.3.6.1.4.1.10106.3.101291.1.1.149
		hxc2000c01v1InAfdDetct OBJECT-TYPE
			SYNTAX Afd1
			MAX-ACCESS read-only
			STATUS current
			DESCRIPTION
				"Input detected AFD"
		::= { hxc2000c01v1Entry 149 }

		-- 1.3.6.1.4.1.10106.3.101291.1.1.150
		hxc2000c01v1InAfdDetctTrapEnable OBJECT-TYPE
			SYNTAX AlarmEnable
			MAX-ACCESS read-write
			STATUS current
			DESCRIPTION
				"Input detected AFD Trap Enable"
		::= { hxc2000c01v1Entry 150 }

		-- 1.3.6.1.4.1.10106.3.101291.1.1.151
		hxc2000c01v1InCfDetct OBJECT-TYPE
			SYNTAX Cf1
			MAX-ACCESS read-only
			STATUS current
			DESCRIPTION
				"Input detected coded frame"
		::= { hxc2000c01v1Entry 151 }

		-- 1.3.6.1.4.1.10106.3.101291.1.1.152
		hxc2000c01v1InCfDetctTrapEnable OBJECT-TYPE
			SYNTAX AlarmEnable
			MAX-ACCESS read-write
			STATUS current
			DESCRIPTION
				"Input detected coded frame Trap Enable"
		::= { hxc2000c01v1Entry 152 }

		-- 1.3.6.1.4.1.10106.3.101291.1.1.153
		hxc2000c01v1InFormat OBJECT-TYPE
			SYNTAX SdiHd3gFmt3
			MAX-ACCESS read-only
			STATUS current
			DESCRIPTION
				"Input format"
		::= { hxc2000c01v1Entry 153 }

		-- 1.3.6.1.4.1.10106.3.101291.1.1.154
		hxc2000c01v1InFormatTrapEnable OBJECT-TYPE
			SYNTAX AlarmEnable
			MAX-ACCESS read-write
			STATUS current
			DESCRIPTION
				"Input format Trap Enable"
		::= { hxc2000c01v1Entry 154 }

		-- 1.3.6.1.4.1.10106.3.101291.1.1.155
		hxc2000c01v1RefFormat OBJECT-TYPE
			SYNTAX SdiHd3gFmt3
			MAX-ACCESS read-only
			STATUS current
			DESCRIPTION
				"Reference format"
		::= { hxc2000c01v1Entry 155 }

		-- 1.3.6.1.4.1.10106.3.101291.1.1.156
		hxc2000c01v1RefFormatTrapEnable OBJECT-TYPE
			SYNTAX AlarmEnable
			MAX-ACCESS read-write
			STATUS current
			DESCRIPTION
				"Reference format Trap Enable"
		::= { hxc2000c01v1Entry 156 }

		-- 1.3.6.1.4.1.10106.3.101291.1.1.157
		hxc2000c01v1TxFormat OBJECT-TYPE
			SYNTAX SdiHd3gFmt3
			MAX-ACCESS read-only
			STATUS current
			DESCRIPTION
				"Output format"
		::= { hxc2000c01v1Entry 157 }

		-- 1.3.6.1.4.1.10106.3.101291.1.1.158
		hxc2000c01v1TxFormatTrapEnable OBJECT-TYPE
			SYNTAX AlarmEnable
			MAX-ACCESS read-write
			STATUS current
			DESCRIPTION
				"Output format Trap Enable"
		::= { hxc2000c01v1Entry 158 }

		-- 1.3.6.1.4.1.10106.3.101291.1.1.159
		hxc2000c01v1TxtPres OBJECT-TYPE
			SYNTAX BitFailN
			MAX-ACCESS read-only
			STATUS current
			DESCRIPTION
				"TXT presence"
		::= { hxc2000c01v1Entry 159 }

		-- 1.3.6.1.4.1.10106.3.101291.1.1.161
		hxc2000c01v1VitcPres OBJECT-TYPE
			SYNTAX BitFailN
			MAX-ACCESS read-only
			STATUS current
			DESCRIPTION
				"VITC presence"
		::= { hxc2000c01v1Entry 161 }

		-- 1.3.6.1.4.1.10106.3.101291.1.1.163
		hxc2000c01v1Mute OBJECT-TYPE
			SYNTAX Bit0No1Yes
			MAX-ACCESS read-only
			STATUS current
			DESCRIPTION
				"Muted output"
		::= { hxc2000c01v1Entry 163 }

		-- 1.3.6.1.4.1.10106.3.101291.1.1.165
		hxc2000c01v1Black OBJECT-TYPE
			SYNTAX Bit0No1Yes
			MAX-ACCESS read-only
			STATUS current
			DESCRIPTION
				"Black output"
		::= { hxc2000c01v1Entry 165 }

		-- 1.3.6.1.4.1.10106.3.101291.1.1.167
		hxc2000c01v1Gpi1 OBJECT-TYPE
			SYNTAX Bit0Off1On
			MAX-ACCESS read-only
			STATUS current
			DESCRIPTION
				"Transmitted GPI1"
		::= { hxc2000c01v1Entry 167 }

		-- 1.3.6.1.4.1.10106.3.101291.1.1.169
		hxc2000c01v1Gpi2 OBJECT-TYPE
			SYNTAX Bit0Off1On
			MAX-ACCESS read-only
			STATUS current
			DESCRIPTION
				"Transmitted GPI2"
		::= { hxc2000c01v1Entry 169 }

		-- 1.3.6.1.4.1.10106.3.101291.1.1.171
		hxc2000c01v1Gpi3 OBJECT-TYPE
			SYNTAX Bit0Off1On
			MAX-ACCESS read-only
			STATUS current
			DESCRIPTION
				"Transmitted GPI3"
		::= { hxc2000c01v1Entry 171 }

		-- 1.3.6.1.4.1.10106.3.101291.1.1.173
		hxc2000c01v1Gpi4 OBJECT-TYPE
			SYNTAX Bit0Off1On
			MAX-ACCESS read-only
			STATUS current
			DESCRIPTION
				"Transmitted GPI4"
		::= { hxc2000c01v1Entry 173 }

		-- 1.3.6.1.4.1.10106.3.101291.1.1.175
		hxc2000c01v1SerialNo OBJECT-TYPE
			SYNTAX SerialNo
			MAX-ACCESS read-only
			STATUS current
			DESCRIPTION
				"Serial number"
		::= { hxc2000c01v1Entry 175 }

		-- 1.3.6.1.4.1.10106.3.101291.1.1.177
		hxc2000c01v1MuteEna OBJECT-TYPE
			SYNTAX Bit0No1Yes
			MAX-ACCESS read-write
			STATUS current
			DESCRIPTION
				"Enables outputs mute"
		::= { hxc2000c01v1Entry 177 }

		-- 1.3.6.1.4.1.10106.3.555601
		uop2000c01v1 OBJECT IDENTIFIER ::= { albalaProducts 555601 }

		-- 1.3.6.1.4.1.10106.3.555601.1
		uop2000c01v1Table  OBJECT-TYPE
			SYNTAX SEQUENCE OF Uop2000c01v1Entry
			MAX-ACCESS not-accessible
			STATUS current
			DESCRIPTION
				"Module  UOP2000C01V1 Table"
			::= { uop2000c01v1 1 }

		-- 1.3.6.1.4.1.10106.3.555601.1.1
		uop2000c01v1Entry  OBJECT-TYPE
			SYNTAX Uop2000c01v1Entry
			MAX-ACCESS not-accessible
			STATUS current
			DESCRIPTION
				"Module UOP2000C01V1 Entry"
			INDEX { uop2000c01v1Index }
			::= { uop2000c01v1Table 1 }

			Uop2000c01v1Entry ::=
			SEQUENCE {
				uop2000c01v1Index
				ModuleIndex,
				uop2000c01v1InputA
				UopInput,
				uop2000c01v1InputATrapEnable
				AlarmEnable,
				uop2000c01v1InputB
				UopInput,
				uop2000c01v1InputBTrapEnable
				AlarmEnable,
				uop2000c01v1BckTxEnA
				Bit0Dis1Ena,
				uop2000c01v1BckTxEnB
				Bit0Dis1Ena,
				uop2000c01v1ForceSfpType
				SfpType1,
				uop2000c01v1ManualMode
				Bit0Aut1Man,
				uop2000c01v1LosA
				BitFail,
				uop2000c01v1LosATrapEnable
				AlarmEnable,
				uop2000c01v1UnlockA
				BitFail,
				uop2000c01v1UnlockATrapEnable
				AlarmEnable,
				uop2000c01v1RateA
				UopRate,
				uop2000c01v1RateATrapEnable
				AlarmEnable,
				uop2000c01v1LosB
				BitFail,
				uop2000c01v1LosBTrapEnable
				AlarmEnable,
				uop2000c01v1UnlockB
				BitFail,
				uop2000c01v1UnlockBTrapEnable
				AlarmEnable,
				uop2000c01v1RateB
				UopRate,
				uop2000c01v1RateBTrapEnable
				AlarmEnable,
				uop2000c01v1SfpType
				SfpType1,
				uop2000c01v1WavelengthA
				Wavelength1,
				uop2000c01v1WavelengthB
				Wavelength1,
				uop2000c01v1Temp
				Uint8,
				uop2000c01v1PowerA
				OptPowerX2Uw,
				uop2000c01v1PowerB
				OptPowerX2Uw,
				uop2000c01v1SerialNo
				SerialNo
			 }

		-- 1.3.6.1.4.1.10106.3.101291.1.1.1
		uop2000c01v1Index OBJECT-TYPE
			SYNTAX ModuleIndex
			MAX-ACCESS read-only
			STATUS current
			DESCRIPTION
				"Index of UOP2000C01V1 Table"
		::= { uop2000c01v1Entry 1 }

		-- 1.3.6.1.4.1.10106.3.101291.1.1.3
		uop2000c01v1InputA OBJECT-TYPE
			SYNTAX UopInput
			MAX-ACCESS read-write
			STATUS current
			DESCRIPTION
				"Indicates the input selected"
		::= { uop2000c01v1Entry 3 }

		-- 1.3.6.1.4.1.10106.3.101291.1.1.4
		uop2000c01v1InputATrapEnable OBJECT-TYPE
			SYNTAX AlarmEnable
			MAX-ACCESS read-write
			STATUS current
			DESCRIPTION
				"Indicates the input selected Trap Enable"
		::= { uop2000c01v1Entry 4 }

		-- 1.3.6.1.4.1.10106.3.101291.1.1.5
		uop2000c01v1InputB OBJECT-TYPE
			SYNTAX UopInput
			MAX-ACCESS read-write
			STATUS current
			DESCRIPTION
				"Indicates the input selected"
		::= { uop2000c01v1Entry 5 }

		-- 1.3.6.1.4.1.10106.3.101291.1.1.6
		uop2000c01v1InputBTrapEnable OBJECT-TYPE
			SYNTAX AlarmEnable
			MAX-ACCESS read-write
			STATUS current
			DESCRIPTION
				"Indicates the input selected Trap Enable"
		::= { uop2000c01v1Entry 6 }

		-- 1.3.6.1.4.1.10106.3.101291.1.1.7
		uop2000c01v1BckTxEnA OBJECT-TYPE
			SYNTAX Bit0Dis1Ena
			MAX-ACCESS read-write
			STATUS current
			DESCRIPTION
				"Enables the driver that transmit to backplane"
		::= { uop2000c01v1Entry 7 }

		-- 1.3.6.1.4.1.10106.3.101291.1.1.9
		uop2000c01v1BckTxEnB OBJECT-TYPE
			SYNTAX Bit0Dis1Ena
			MAX-ACCESS read-write
			STATUS current
			DESCRIPTION
				"Enables the driver that transmit to backplane"
		::= { uop2000c01v1Entry 9 }

		-- 1.3.6.1.4.1.10106.3.101291.1.1.11
		uop2000c01v1ForceSfpType OBJECT-TYPE
			SYNTAX SfpType1
			MAX-ACCESS read-write
			STATUS current
			DESCRIPTION
				"Enables forcing SFP type when it is unknown"
		::= { uop2000c01v1Entry 11 }

		-- 1.3.6.1.4.1.10106.3.101291.1.1.13
		uop2000c01v1ManualMode OBJECT-TYPE
			SYNTAX Bit0Aut1Man
			MAX-ACCESS read-write
			STATUS current
			DESCRIPTION
				"Operating mode"
		::= { uop2000c01v1Entry 13 }

		-- 1.3.6.1.4.1.10106.3.101291.1.1.15
		uop2000c01v1LosA OBJECT-TYPE
			SYNTAX BitFail
			MAX-ACCESS read-only
			STATUS current
			DESCRIPTION
				"Indicates a loss of signal"
		::= { uop2000c01v1Entry 15 }

		-- 1.3.6.1.4.1.10106.3.101291.1.1.16
		uop2000c01v1LosATrapEnable OBJECT-TYPE
			SYNTAX AlarmEnable
			MAX-ACCESS read-write
			STATUS current
			DESCRIPTION
				"Indicates a loss of signal Trap Enable"
		::= { uop2000c01v1Entry 16 }

		-- 1.3.6.1.4.1.10106.3.101291.1.1.17
		uop2000c01v1UnlockA OBJECT-TYPE
			SYNTAX BitFail
			MAX-ACCESS read-only
			STATUS current
			DESCRIPTION
				"Indicates signal unlock fail"
		::= { uop2000c01v1Entry 17 }

		-- 1.3.6.1.4.1.10106.3.101291.1.1.18
		uop2000c01v1UnlockATrapEnable OBJECT-TYPE
			SYNTAX AlarmEnable
			MAX-ACCESS read-write
			STATUS current
			DESCRIPTION
				"Indicates signal unlock fail Trap Enable"
		::= { uop2000c01v1Entry 18 }

		-- 1.3.6.1.4.1.10106.3.101291.1.1.19
		uop2000c01v1RateA OBJECT-TYPE
			SYNTAX UopRate
			MAX-ACCESS read-only
			STATUS current
			DESCRIPTION
				"Indicates the SDI signal type"
		::= { uop2000c01v1Entry 19 }

		-- 1.3.6.1.4.1.10106.3.101291.1.1.20
		uop2000c01v1RateATrapEnable OBJECT-TYPE
			SYNTAX AlarmEnable
			MAX-ACCESS read-write
			STATUS current
			DESCRIPTION
				"Indicates the SDI signal type Trap Enable"
		::= { uop2000c01v1Entry 20 }

		-- 1.3.6.1.4.1.10106.3.101291.1.1.21
		uop2000c01v1LosB OBJECT-TYPE
			SYNTAX BitFail
			MAX-ACCESS read-only
			STATUS current
			DESCRIPTION
				"Indicates a loss of signal"
		::= { uop2000c01v1Entry 21 }

		-- 1.3.6.1.4.1.10106.3.101291.1.1.22
		uop2000c01v1LosBTrapEnable OBJECT-TYPE
			SYNTAX AlarmEnable
			MAX-ACCESS read-write
			STATUS current
			DESCRIPTION
				"Indicates a loss of signal Trap Enable"
		::= { uop2000c01v1Entry 22 }

		-- 1.3.6.1.4.1.10106.3.101291.1.1.23
		uop2000c01v1UnlockB OBJECT-TYPE
			SYNTAX BitFail
			MAX-ACCESS read-only
			STATUS current
			DESCRIPTION
				"Indicates signal unlock fail"
		::= { uop2000c01v1Entry 23 }

		-- 1.3.6.1.4.1.10106.3.101291.1.1.24
		uop2000c01v1UnlockBTrapEnable OBJECT-TYPE
			SYNTAX AlarmEnable
			MAX-ACCESS read-write
			STATUS current
			DESCRIPTION
				"Indicates signal unlock fail Trap Enable"
		::= { uop2000c01v1Entry 24 }

		-- 1.3.6.1.4.1.10106.3.101291.1.1.25
		uop2000c01v1RateB OBJECT-TYPE
			SYNTAX UopRate
			MAX-ACCESS read-only
			STATUS current
			DESCRIPTION
				"Indicates the SDI signal type"
		::= { uop2000c01v1Entry 25 }

		-- 1.3.6.1.4.1.10106.3.101291.1.1.26
		uop2000c01v1RateBTrapEnable OBJECT-TYPE
			SYNTAX AlarmEnable
			MAX-ACCESS read-write
			STATUS current
			DESCRIPTION
				"Indicates the SDI signal type Trap Enable"
		::= { uop2000c01v1Entry 26 }

		-- 1.3.6.1.4.1.10106.3.101291.1.1.27
		uop2000c01v1SfpType OBJECT-TYPE
			SYNTAX SfpType1
			MAX-ACCESS read-only
			STATUS current
			DESCRIPTION
				"SFP type"
		::= { uop2000c01v1Entry 27 }

		-- 1.3.6.1.4.1.10106.3.101291.1.1.29
		uop2000c01v1WavelengthA OBJECT-TYPE
			SYNTAX Wavelength1
			MAX-ACCESS read-only
			STATUS current
			DESCRIPTION
				"Laser A wavelength"
		::= { uop2000c01v1Entry 29 }

		-- 1.3.6.1.4.1.10106.3.101291.1.1.31
		uop2000c01v1WavelengthB OBJECT-TYPE
			SYNTAX Wavelength1
			MAX-ACCESS read-only
			STATUS current
			DESCRIPTION
				"Laser B wavelength"
		::= { uop2000c01v1Entry 31 }

		-- 1.3.6.1.4.1.10106.3.101291.1.1.33
		uop2000c01v1Temp OBJECT-TYPE
			SYNTAX Uint8
			MAX-ACCESS read-only
			STATUS current
			DESCRIPTION
				"SFP Temperature"
		::= { uop2000c01v1Entry 33 }

		-- 1.3.6.1.4.1.10106.3.101291.1.1.35
		uop2000c01v1PowerA OBJECT-TYPE
			SYNTAX OptPowerX2Uw
			MAX-ACCESS read-only
			STATUS current
			DESCRIPTION
				"Optical A received power"
		::= { uop2000c01v1Entry 35 }

		-- 1.3.6.1.4.1.10106.3.101291.1.1.37
		uop2000c01v1PowerB OBJECT-TYPE
			SYNTAX OptPowerX2Uw
			MAX-ACCESS read-only
			STATUS current
			DESCRIPTION
				"Optical B received power"
		::= { uop2000c01v1Entry 37 }

		-- 1.3.6.1.4.1.10106.3.101291.1.1.39
		uop2000c01v1SerialNo OBJECT-TYPE
			SYNTAX SerialNo
			MAX-ACCESS read-only
			STATUS current
			DESCRIPTION
				"Serial number"
		::= { uop2000c01v1Entry 39 }

		-- 1.3.6.1.4.1.10106.3.557901
		ur-2001r01v1 OBJECT IDENTIFIER ::= { albalaProducts 557901 }

		-- 1.3.6.1.4.1.10106.3.557901.1
		ur-2001r01v1Table  OBJECT-TYPE
			SYNTAX SEQUENCE OF Ur-2001r01v1Entry
			MAX-ACCESS not-accessible
			STATUS current
			DESCRIPTION
				"Module  UR-2001R01V1 Table"
			::= { ur-2001r01v1 1 }

		-- 1.3.6.1.4.1.10106.3.557901.1.1
		ur-2001r01v1Entry  OBJECT-TYPE
			SYNTAX Ur-2001r01v1Entry
			MAX-ACCESS not-accessible
			STATUS current
			DESCRIPTION
				"Module UR-2001R01V1 Entry"
			INDEX { ur-2001r01v1Index }
			::= { ur-2001r01v1Table 1 }

			Ur-2001r01v1Entry ::=
			SEQUENCE {
				ur-2001r01v1Index
				ModuleIndex,
				ur-2001r01v1Psu0Fail
				BitFail,
				ur-2001r01v1Psu1Fail
				BitFail,
				ur-2001r01v1SerialNo
				SerialNo
			 }

		-- 1.3.6.1.4.1.10106.3.101291.1.1.1
		ur-2001r01v1Index OBJECT-TYPE
			SYNTAX ModuleIndex
			MAX-ACCESS read-only
			STATUS current
			DESCRIPTION
				"Index of UR-2001R01V1 Table"
		::= { ur-2001r01v1Entry 1 }

		-- 1.3.6.1.4.1.10106.3.101291.1.1.3
		ur-2001r01v1Psu0Fail OBJECT-TYPE
			SYNTAX BitFail
			MAX-ACCESS read-only
			STATUS current
			DESCRIPTION
				"Indicates fail in power supply 1"
		::= { ur-2001r01v1Entry 3 }

		-- 1.3.6.1.4.1.10106.3.101291.1.1.5
		ur-2001r01v1Psu1Fail OBJECT-TYPE
			SYNTAX BitFail
			MAX-ACCESS read-only
			STATUS current
			DESCRIPTION
				"Indicates fail in power supply 2"
		::= { ur-2001r01v1Entry 5 }

		-- 1.3.6.1.4.1.10106.3.101291.1.1.7
		ur-2001r01v1SerialNo OBJECT-TYPE
			SYNTAX SerialNo
			MAX-ACCESS read-only
			STATUS current
			DESCRIPTION
				"Serial number"
		::= { ur-2001r01v1Entry 7 }

		-- 1.3.6.1.4.1.10106.3.574401
		act2000c01v1 OBJECT IDENTIFIER ::= { albalaProducts 574401 }

		-- 1.3.6.1.4.1.10106.3.574401.1
		act2000c01v1Table  OBJECT-TYPE
			SYNTAX SEQUENCE OF Act2000c01v1Entry
			MAX-ACCESS not-accessible
			STATUS current
			DESCRIPTION
				"Module  ACT2000C01V1 Table"
			::= { act2000c01v1 1 }

		-- 1.3.6.1.4.1.10106.3.574401.1.1
		act2000c01v1Entry  OBJECT-TYPE
			SYNTAX Act2000c01v1Entry
			MAX-ACCESS not-accessible
			STATUS current
			DESCRIPTION
				"Module ACT2000C01V1 Entry"
			INDEX { act2000c01v1Index }
			::= { act2000c01v1Table 1 }

			Act2000c01v1Entry ::=
			SEQUENCE {
				act2000c01v1Index
				ModuleIndex,
				act2000c01v1Mode
				ChgOverMode1,
				act2000c01v1ModeTrapEnable
				AlarmEnable,
				act2000c01v1Buzzer
				BitMask,
				act2000c01v1Input
				ChgOverInput2,
				act2000c01v1InputTrapEnable
				AlarmEnable,
				act2000c01v1InputChange
				Bit0No1Yes,
				act2000c01v1AnaThrLev
				LevelDbu1,
				act2000c01v1AesThrLev
				LevelDbu1,
				act2000c01v1ActTime
				TimeX10Ms2,
				act2000c01v1RecTime
				TimeX10Ms2,
				act2000c01v1InpMainFail
				BitFail,
				act2000c01v1InpMainFailTrapEnable
				AlarmEnable,
				act2000c01v1GpiMainFail
				BitFail,
				act2000c01v1GpiMainFailTrapEnable
				AlarmEnable,
				act2000c01v1InpResFail
				BitFail,
				act2000c01v1InpResFailTrapEnable
				AlarmEnable,
				act2000c01v1GpiResFail
				BitFail,
				act2000c01v1GpiResFailTrapEnable
				AlarmEnable,
				act2000c01v1Gpo1
				Bit0Open1Clo,
				act2000c01v1Gpo2
				Bit0Open1Clo,
				act2000c01v1AvgLevMain
				LevelDbu1,
				act2000c01v1AvgLevRes
				LevelDbu1,
				act2000c01v1PkLevMain
				LevelDbu1,
				act2000c01v1PkLevRes
				LevelDbu1,
				act2000c01v1SerialNo
				SerialNo
			 }

		-- 1.3.6.1.4.1.10106.3.101291.1.1.1
		act2000c01v1Index OBJECT-TYPE
			SYNTAX ModuleIndex
			MAX-ACCESS read-only
			STATUS current
			DESCRIPTION
				"Index of ACT2000C01V1 Table"
		::= { act2000c01v1Entry 1 }

		-- 1.3.6.1.4.1.10106.3.101291.1.1.3
		act2000c01v1Mode OBJECT-TYPE
			SYNTAX ChgOverMode1
			MAX-ACCESS read-write
			STATUS current
			DESCRIPTION
				"Allows selecting the switching mode"
		::= { act2000c01v1Entry 3 }

		-- 1.3.6.1.4.1.10106.3.101291.1.1.4
		act2000c01v1ModeTrapEnable OBJECT-TYPE
			SYNTAX AlarmEnable
			MAX-ACCESS read-write
			STATUS current
			DESCRIPTION
				"Allows selecting the switching mode Trap Enable"
		::= { act2000c01v1Entry 4 }

		-- 1.3.6.1.4.1.10106.3.101291.1.1.5
		act2000c01v1Buzzer OBJECT-TYPE
			SYNTAX BitMask
			MAX-ACCESS read-write
			STATUS current
			DESCRIPTION
				"Allows buzzer operation"
		::= { act2000c01v1Entry 5 }

		-- 1.3.6.1.4.1.10106.3.101291.1.1.7
		act2000c01v1Input OBJECT-TYPE
			SYNTAX ChgOverInput2
			MAX-ACCESS read-write
			STATUS current
			DESCRIPTION
				"Selected input"
		::= { act2000c01v1Entry 7 }

		-- 1.3.6.1.4.1.10106.3.101291.1.1.8
		act2000c01v1InputTrapEnable OBJECT-TYPE
			SYNTAX AlarmEnable
			MAX-ACCESS read-write
			STATUS current
			DESCRIPTION
				"Selected input Trap Enable"
		::= { act2000c01v1Entry 8 }

		-- 1.3.6.1.4.1.10106.3.101291.1.1.9
		act2000c01v1InputChange OBJECT-TYPE
			SYNTAX Bit0No1Yes
			MAX-ACCESS read-write
			STATUS current
			DESCRIPTION
				"Signals a change in selected input"
		::= { act2000c01v1Entry 9 }

		-- 1.3.6.1.4.1.10106.3.101291.1.1.11
		act2000c01v1AnaThrLev OBJECT-TYPE
			SYNTAX LevelDbu1
			MAX-ACCESS read-write
			STATUS current
			DESCRIPTION
				"Allows adjusting the presence threshold level for analog signals"
		::= { act2000c01v1Entry 11 }

		-- 1.3.6.1.4.1.10106.3.101291.1.1.13
		act2000c01v1AesThrLev OBJECT-TYPE
			SYNTAX LevelDbu1
			MAX-ACCESS read-write
			STATUS current
			DESCRIPTION
				"Allows adjusting the presence threshold level for AES signals"
		::= { act2000c01v1Entry 13 }

		-- 1.3.6.1.4.1.10106.3.101291.1.1.15
		act2000c01v1ActTime OBJECT-TYPE
			SYNTAX TimeX10Ms2
			MAX-ACCESS read-write
			STATUS current
			DESCRIPTION
				"Allows adjusting the time from the failure start until it is signaled"
		::= { act2000c01v1Entry 15 }

		-- 1.3.6.1.4.1.10106.3.101291.1.1.17
		act2000c01v1RecTime OBJECT-TYPE
			SYNTAX TimeX10Ms2
			MAX-ACCESS read-write
			STATUS current
			DESCRIPTION
				"Allows adjusting the time from the failure stop until it is signaled"
		::= { act2000c01v1Entry 17 }

		-- 1.3.6.1.4.1.10106.3.101291.1.1.19
		act2000c01v1InpMainFail OBJECT-TYPE
			SYNTAX BitFail
			MAX-ACCESS read-only
			STATUS current
			DESCRIPTION
				"Main input status"
		::= { act2000c01v1Entry 19 }

		-- 1.3.6.1.4.1.10106.3.101291.1.1.20
		act2000c01v1InpMainFailTrapEnable OBJECT-TYPE
			SYNTAX AlarmEnable
			MAX-ACCESS read-write
			STATUS current
			DESCRIPTION
				"Main input status Trap Enable"
		::= { act2000c01v1Entry 20 }

		-- 1.3.6.1.4.1.10106.3.101291.1.1.21
		act2000c01v1GpiMainFail OBJECT-TYPE
			SYNTAX BitFail
			MAX-ACCESS read-only
			STATUS current
			DESCRIPTION
				"GPI main input status"
		::= { act2000c01v1Entry 21 }

		-- 1.3.6.1.4.1.10106.3.101291.1.1.22
		act2000c01v1GpiMainFailTrapEnable OBJECT-TYPE
			SYNTAX AlarmEnable
			MAX-ACCESS read-write
			STATUS current
			DESCRIPTION
				"GPI main input status Trap Enable"
		::= { act2000c01v1Entry 22 }

		-- 1.3.6.1.4.1.10106.3.101291.1.1.23
		act2000c01v1InpResFail OBJECT-TYPE
			SYNTAX BitFail
			MAX-ACCESS read-only
			STATUS current
			DESCRIPTION
				"Reserve input status"
		::= { act2000c01v1Entry 23 }

		-- 1.3.6.1.4.1.10106.3.101291.1.1.24
		act2000c01v1InpResFailTrapEnable OBJECT-TYPE
			SYNTAX AlarmEnable
			MAX-ACCESS read-write
			STATUS current
			DESCRIPTION
				"Reserve input status Trap Enable"
		::= { act2000c01v1Entry 24 }

		-- 1.3.6.1.4.1.10106.3.101291.1.1.25
		act2000c01v1GpiResFail OBJECT-TYPE
			SYNTAX BitFail
			MAX-ACCESS read-only
			STATUS current
			DESCRIPTION
				"GPI main input status"
		::= { act2000c01v1Entry 25 }

		-- 1.3.6.1.4.1.10106.3.101291.1.1.26
		act2000c01v1GpiResFailTrapEnable OBJECT-TYPE
			SYNTAX AlarmEnable
			MAX-ACCESS read-write
			STATUS current
			DESCRIPTION
				"GPI main input status Trap Enable"
		::= { act2000c01v1Entry 26 }

		-- 1.3.6.1.4.1.10106.3.101291.1.1.27
		act2000c01v1Gpo1 OBJECT-TYPE
			SYNTAX Bit0Open1Clo
			MAX-ACCESS read-only
			STATUS current
			DESCRIPTION
				"GPO1 state"
		::= { act2000c01v1Entry 27 }

		-- 1.3.6.1.4.1.10106.3.101291.1.1.29
		act2000c01v1Gpo2 OBJECT-TYPE
			SYNTAX Bit0Open1Clo
			MAX-ACCESS read-only
			STATUS current
			DESCRIPTION
				"GPO2 state"
		::= { act2000c01v1Entry 29 }

		-- 1.3.6.1.4.1.10106.3.101291.1.1.31
		act2000c01v1AvgLevMain OBJECT-TYPE
			SYNTAX LevelDbu1
			MAX-ACCESS read-only
			STATUS current
			DESCRIPTION
				"Main average level"
		::= { act2000c01v1Entry 31 }

		-- 1.3.6.1.4.1.10106.3.101291.1.1.33
		act2000c01v1AvgLevRes OBJECT-TYPE
			SYNTAX LevelDbu1
			MAX-ACCESS read-only
			STATUS current
			DESCRIPTION
				"Reserve average level"
		::= { act2000c01v1Entry 33 }

		-- 1.3.6.1.4.1.10106.3.101291.1.1.35
		act2000c01v1PkLevMain OBJECT-TYPE
			SYNTAX LevelDbu1
			MAX-ACCESS read-only
			STATUS current
			DESCRIPTION
				"Main peak level"
		::= { act2000c01v1Entry 35 }

		-- 1.3.6.1.4.1.10106.3.101291.1.1.37
		act2000c01v1PkLevRes OBJECT-TYPE
			SYNTAX LevelDbu1
			MAX-ACCESS read-only
			STATUS current
			DESCRIPTION
				"Reserve peak level"
		::= { act2000c01v1Entry 37 }

		-- 1.3.6.1.4.1.10106.3.101291.1.1.39
		act2000c01v1SerialNo OBJECT-TYPE
			SYNTAX SerialNo
			MAX-ACCESS read-only
			STATUS current
			DESCRIPTION
				"Serial number"
		::= { act2000c01v1Entry 39 }

		-- 1.3.6.1.4.1.10106.3.577901
		utg2000c01v1 OBJECT IDENTIFIER ::= { albalaProducts 577901 }

		-- 1.3.6.1.4.1.10106.3.577901.1
		utg2000c01v1Table  OBJECT-TYPE
			SYNTAX SEQUENCE OF Utg2000c01v1Entry
			MAX-ACCESS not-accessible
			STATUS current
			DESCRIPTION
				"Module  UTG2000C01V1 Table"
			::= { utg2000c01v1 1 }

		-- 1.3.6.1.4.1.10106.3.577901.1.1
		utg2000c01v1Entry  OBJECT-TYPE
			SYNTAX Utg2000c01v1Entry
			MAX-ACCESS not-accessible
			STATUS current
			DESCRIPTION
				"Module UTG2000C01V1 Entry"
			INDEX { utg2000c01v1Index }
			::= { utg2000c01v1Table 1 }

			Utg2000c01v1Entry ::=
			SEQUENCE {
				utg2000c01v1Index
				ModuleIndex,
				utg2000c01v1ActivePreset
				Preset16Active,
				utg2000c01v1LoadPreset
				Preset16Load,
				utg2000c01v1SavePreset
				Preset16Save,
				utg2000c01v1SdiRefInput
				Bit0Opt1Ele,
				utg2000c01v1OutputFormat
				SdiHd12gFmt2,
				utg2000c01v1Pattern
				Uint6,
				utg2000c01v1RstErrors
				BitMask,
				utg2000c01v1ExpRefFormat
				SdiHd12gFmt2,
				utg2000c01v1ExpRefFormatTrapEnable
				AlarmEnable,
				utg2000c01v1RefInput
				RefSel1,
				utg2000c01v1RefInputTrapEnable
				AlarmEnable,
				utg2000c01v1MeasInput
				RefSel1,
				utg2000c01v1HDelay
				DelayPixel4,
				utg2000c01v1VDelay
				DelayLines3,
				utg2000c01v1AvDlyBlack
				LumaUint8,
				utg2000c01v1AvDlySil
				LevelDbfs2x,
				utg2000c01v1OsdDlyEn
				Bit0No1Yes,
				utg2000c01v1Pwm
				Uint8X,
				utg2000c01v1OverlayIo1
				Bit0No1Yes,
				utg2000c01v1OverlayIo2
				Bit0No1Yes,
				utg2000c01v1OverlayIo3
				Bit0No1Yes,
				utg2000c01v1OverlayIo4
				Bit0No1Yes,
				utg2000c01v1OverlayOptout
				Bit0No1Yes,
				utg2000c01v1EnLogo11
				Bit0No1Yes,
				utg2000c01v1IdLogo11
				Uint8,
				utg2000c01v1XoffLogo11
				DelayPixel4,
				utg2000c01v1YoffLogo11
				DelayLines3,
				utg2000c01v1EnLogo21
				Bit0No1Yes,
				utg2000c01v1IdLogo21
				Uint8,
				utg2000c01v1XoffLogo21
				DelayPixel4,
				utg2000c01v1YoffLogo21
				DelayLines3,
				utg2000c01v1EnOsd1
				Bit0No1Yes,
				utg2000c01v1Osd1Size
				Size3,
				utg2000c01v1EnOsd2
				Bit0No1Yes,
				utg2000c01v1Osd2Size
				Size3,
				utg2000c01v1Osd1MovEna
				Bit0No1Yes,
				utg2000c01v1Osd1SpeedH
				Uint4,
				utg2000c01v1Osd1SpeedV
				Uint4,
				utg2000c01v1Osd1StartH
				DelayPixel5,
				utg2000c01v1Osd1StartV
				DelayLines3,
				utg2000c01v1Osd1EndH
				DelayPixel5,
				utg2000c01v1Osd1EndV
				DelayLines3,
				utg2000c01v1EnAudIm1
				Bit0No1Yes,
				utg2000c01v1EnAudIm2
				Bit0No1Yes,
				utg2000c01v1EnAudIm3
				Bit0No1Yes,
				utg2000c01v1EnAudIm4
				Bit0No1Yes,
				utg2000c01v1EnGrp1Aud0
				Bit0No1Yes,
				utg2000c01v1EnGrp2Aud0
				Bit0No1Yes,
				utg2000c01v1EnGrp3Aud0
				Bit0No1Yes,
				utg2000c01v1EnGrp4Aud0
				Bit0No1Yes,
				utg2000c01v1VidDip0
				Bit0No1Yes,
				utg2000c01v1AudFrP0G00
				AudioFreq1,
				utg2000c01v1AudFrP1G00
				AudioFreq1,
				utg2000c01v1AudFrP0G10
				AudioFreq1,
				utg2000c01v1AudFrP1G10
				AudioFreq1,
				utg2000c01v1AudFrP0G20
				AudioFreq1,
				utg2000c01v1AudFrP1G20
				AudioFreq1,
				utg2000c01v1AudFrP0G30
				AudioFreq1,
				utg2000c01v1AudFrP1G30
				AudioFreq1,
				utg2000c01v1AudDipP0G00
				Bit0Dis1Ena,
				utg2000c01v1AudDipP1G00
				Bit0Dis1Ena,
				utg2000c01v1AudDipP0G10
				Bit0Dis1Ena,
				utg2000c01v1AudDipP1G10
				Bit0Dis1Ena,
				utg2000c01v1AudDipP0G20
				Bit0Dis1Ena,
				utg2000c01v1AudDipP1G20
				Bit0Dis1Ena,
				utg2000c01v1AudDipP0G30
				Bit0Dis1Ena,
				utg2000c01v1AudDipP1G30
				Bit0Dis1Ena,
				utg2000c01v1AudLevP0G00
				AudioLev0,
				utg2000c01v1AudLevP0G10
				AudioLev0,
				utg2000c01v1AudLevP1G00
				AudioLev0,
				utg2000c01v1AudLevP1G10
				AudioLev0,
				utg2000c01v1AudLevP0G20
				AudioLev0,
				utg2000c01v1AudLevP1G20
				AudioLev0,
				utg2000c01v1AudLevP0G30
				AudioLev0,
				utg2000c01v1AudLevP1G30
				AudioLev0,
				utg2000c01v1DropFrame
				BitMask,
				utg2000c01v1Bgf
				BgfBits,
				utg2000c01v1DateFormat
				DateFmt,
				utg2000c01v1EnDateGen
				BitMask,
				utg2000c01v1AdjHourDay
				Uint5,
				utg2000c01v1SumMonthSt
				Month,
				utg2000c01v1SumWeekSt
				WeekOfMonth,
				utg2000c01v1SumWDaySt
				Day,
				utg2000c01v1SumHourSt
				TimeH1,
				utg2000c01v1SumHourOffset
				Int8,
				utg2000c01v1WinMonthSt
				Month,
				utg2000c01v1WinWeekSt
				WeekOfMonth,
				utg2000c01v1WinWDaySt
				Day,
				utg2000c01v1WinHourSt
				TimeH1,
				utg2000c01v1WinHourOffset
				Int8,
				utg2000c01v1EnDlsave
				BitMask,
				utg2000c01v1Delay1G1p0l
				DelayX1Ms,
				utg2000c01v1Delay1G1p0r
				DelayX1Ms,
				utg2000c01v1Delay1G1p1l
				DelayX1Ms,
				utg2000c01v1Delay1G1p1r
				DelayX1Ms,
				utg2000c01v1Delay1G2p0l
				DelayX1Ms,
				utg2000c01v1Delay1G2p0r
				DelayX1Ms,
				utg2000c01v1Delay1G2p1l
				DelayX1Ms,
				utg2000c01v1Delay1G2p1r
				DelayX1Ms,
				utg2000c01v1Delay1G3p0l
				DelayX1Ms,
				utg2000c01v1Delay1G3p0r
				DelayX1Ms,
				utg2000c01v1Delay1G3p1l
				DelayX1Ms,
				utg2000c01v1Delay1G3p1r
				DelayX1Ms,
				utg2000c01v1Delay1G4p0l
				DelayX1Ms,
				utg2000c01v1Delay1G4p0r
				DelayX1Ms,
				utg2000c01v1Delay1G4p1l
				DelayX1Ms,
				utg2000c01v1Delay1G4p1r
				DelayX1Ms,
				utg2000c01v1Av1SeqG1p0
				BitFail,
				utg2000c01v1Av1SeqG1p1
				BitFail,
				utg2000c01v1Av1SeqG2p0
				BitFail,
				utg2000c01v1Av1SeqG2p1
				BitFail,
				utg2000c01v1Av1SeqG3p0
				BitFail,
				utg2000c01v1Av1SeqG3p1
				BitFail,
				utg2000c01v1Av1SeqG4p0
				BitFail,
				utg2000c01v1Av1SeqG4p1
				BitFail,
				utg2000c01v1Aud1GrpPres1
				BitFailN,
				utg2000c01v1Aud1GrpPres2
				BitFailN,
				utg2000c01v1Aud1GrpPres3
				BitFailN,
				utg2000c01v1Aud1GrpPres4
				BitFailN,
				utg2000c01v1Av1SeqPhase
				Uint8,
				utg2000c01v1Delay2G1p0l
				DelayX1Ms,
				utg2000c01v1Delay2G1p0r
				DelayX1Ms,
				utg2000c01v1Delay2G1p1l
				DelayX1Ms,
				utg2000c01v1Delay2G1p1r
				DelayX1Ms,
				utg2000c01v1Delay2G2p0l
				DelayX1Ms,
				utg2000c01v1Delay2G2p0r
				DelayX1Ms,
				utg2000c01v1Delay2G2p1l
				DelayX1Ms,
				utg2000c01v1Delay2G2p1r
				DelayX1Ms,
				utg2000c01v1Delay2G3p0l
				DelayX1Ms,
				utg2000c01v1Delay2G3p0r
				DelayX1Ms,
				utg2000c01v1Delay2G3p1l
				DelayX1Ms,
				utg2000c01v1Delay2G3p1r
				DelayX1Ms,
				utg2000c01v1Delay2G4p0l
				DelayX1Ms,
				utg2000c01v1Delay2G4p0r
				DelayX1Ms,
				utg2000c01v1Delay2G4p1l
				DelayX1Ms,
				utg2000c01v1Delay2G4p1r
				DelayX1Ms,
				utg2000c01v1Av2SeqG1p0
				BitFail,
				utg2000c01v1Av2SeqG1p1
				BitFail,
				utg2000c01v1Av2SeqG2p0
				BitFail,
				utg2000c01v1Av2SeqG2p1
				BitFail,
				utg2000c01v1Av2SeqG3p0
				BitFail,
				utg2000c01v1Av2SeqG3p1
				BitFail,
				utg2000c01v1Av2SeqG4p0
				BitFail,
				utg2000c01v1Av2SeqG4p1
				BitFail,
				utg2000c01v1Aud2GrpPres1
				BitFailN,
				utg2000c01v1Aud2GrpPres2
				BitFailN,
				utg2000c01v1Aud2GrpPres3
				BitFailN,
				utg2000c01v1Aud2GrpPres4
				BitFailN,
				utg2000c01v1Av2SeqPhase
				Uint8,
				utg2000c01v1Delay3G1p0l
				DelayX1Ms,
				utg2000c01v1Delay3G1p0r
				DelayX1Ms,
				utg2000c01v1Delay3G1p1l
				DelayX1Ms,
				utg2000c01v1Delay3G1p1r
				DelayX1Ms,
				utg2000c01v1Delay3G2p0l
				DelayX1Ms,
				utg2000c01v1Delay3G2p0r
				DelayX1Ms,
				utg2000c01v1Delay3G2p1l
				DelayX1Ms,
				utg2000c01v1Delay3G2p1r
				DelayX1Ms,
				utg2000c01v1Delay3G3p0l
				DelayX1Ms,
				utg2000c01v1Delay3G3p0r
				DelayX1Ms,
				utg2000c01v1Delay3G3p1l
				DelayX1Ms,
				utg2000c01v1Delay3G3p1r
				DelayX1Ms,
				utg2000c01v1Delay3G4p0l
				DelayX1Ms,
				utg2000c01v1Delay3G4p0r
				DelayX1Ms,
				utg2000c01v1Delay3G4p1l
				DelayX1Ms,
				utg2000c01v1Delay3G4p1r
				DelayX1Ms,
				utg2000c01v1Av3SeqG1p0
				BitFail,
				utg2000c01v1Av3SeqG1p1
				BitFail,
				utg2000c01v1Av3SeqG2p0
				BitFail,
				utg2000c01v1Av3SeqG2p1
				BitFail,
				utg2000c01v1Av3SeqG3p0
				BitFail,
				utg2000c01v1Av3SeqG3p1
				BitFail,
				utg2000c01v1Av3SeqG4p0
				BitFail,
				utg2000c01v1Av3SeqG4p1
				BitFail,
				utg2000c01v1Aud3GrpPres1
				BitFailN,
				utg2000c01v1Aud3GrpPres2
				BitFailN,
				utg2000c01v1Aud3GrpPres3
				BitFailN,
				utg2000c01v1Aud3GrpPres4
				BitFailN,
				utg2000c01v1Av3SeqPhase
				Uint8,
				utg2000c01v1DelayG1p0l
				DelayX1Ms,
				utg2000c01v1DelayG1p0r
				DelayX1Ms,
				utg2000c01v1DelayG1p1l
				DelayX1Ms,
				utg2000c01v1DelayG1p1r
				DelayX1Ms,
				utg2000c01v1DelayG2p0l
				DelayX1Ms,
				utg2000c01v1DelayG2p0r
				DelayX1Ms,
				utg2000c01v1DelayG2p1l
				DelayX1Ms,
				utg2000c01v1DelayG2p1r
				DelayX1Ms,
				utg2000c01v1DelayG3p0l
				DelayX1Ms,
				utg2000c01v1DelayG3p0r
				DelayX1Ms,
				utg2000c01v1DelayG3p1l
				DelayX1Ms,
				utg2000c01v1DelayG3p1r
				DelayX1Ms,
				utg2000c01v1DelayG4p0l
				DelayX1Ms,
				utg2000c01v1DelayG4p0r
				DelayX1Ms,
				utg2000c01v1DelayG4p1l
				DelayX1Ms,
				utg2000c01v1DelayG4p1r
				DelayX1Ms,
				utg2000c01v1AvSeqG1p0
				BitFail,
				utg2000c01v1AvSeqG1p1
				BitFail,
				utg2000c01v1AvSeqG2p0
				BitFail,
				utg2000c01v1AvSeqG2p1
				BitFail,
				utg2000c01v1AvSeqG3p0
				BitFail,
				utg2000c01v1AvSeqG3p1
				BitFail,
				utg2000c01v1AvSeqG4p0
				BitFail,
				utg2000c01v1AvSeqG4p1
				BitFail,
				utg2000c01v1AudGrpPres1
				BitFailN,
				utg2000c01v1AudGrpPres2
				BitFailN,
				utg2000c01v1AudGrpPres3
				BitFailN,
				utg2000c01v1AudGrpPres4
				BitFailN,
				utg2000c01v1AvSeqPhase
				Uint8,
				utg2000c01v1ArefFail
				BitFail,
				utg2000c01v1ArefFailTrapEnable
				AlarmEnable,
				utg2000c01v1DrefFail
				BitFail,
				utg2000c01v1DrefFailTrapEnable
				AlarmEnable,
				utg2000c01v1IrefFail
				BitFail,
				utg2000c01v1IrefFailTrapEnable
				AlarmEnable,
				utg2000c01v1RefIncFail
				BitFail,
				utg2000c01v1RefIncFailTrapEnable
				AlarmEnable,
				utg2000c01v1RefLockFail
				BitFail,
				utg2000c01v1RefLockFailTrapEnable
				AlarmEnable,
				utg2000c01v1DrefCrcFail
				BitFail,
				utg2000c01v1DrefCrcFailTrapEnable
				AlarmEnable,
				utg2000c01v1TcFail
				BitFail,
				utg2000c01v1LogoRdy1
				Bit0No1Yes,
				utg2000c01v1ArefFormat
				SdiHd12gFmt2,
				utg2000c01v1ArefFormatTrapEnable
				AlarmEnable,
				utg2000c01v1DrefFormat
				SdiHd12gFmt2,
				utg2000c01v1DrefFormatTrapEnable
				AlarmEnable,
				utg2000c01v1CrcErrors
				Uint8,
				utg2000c01v1InputFailures
				Uint8,
				utg2000c01v1MeasDelay
				DelayX74Ns,
				utg2000c01v1MeasFreq
				FrqDrft3,
				utg2000c01v1SfpType
				SfpType2,
				utg2000c01v1SfpTemp
				Temperature0c1,
				utg2000c01v1SfpRxPower
				OptPowerX2Uw,
				utg2000c01v1SerialNo
				SerialNo
			 }

		-- 1.3.6.1.4.1.10106.3.101291.1.1.1
		utg2000c01v1Index OBJECT-TYPE
			SYNTAX ModuleIndex
			MAX-ACCESS read-only
			STATUS current
			DESCRIPTION
				"Index of UTG2000C01V1 Table"
		::= { utg2000c01v1Entry 1 }

		-- 1.3.6.1.4.1.10106.3.101291.1.1.3
		utg2000c01v1ActivePreset OBJECT-TYPE
			SYNTAX Preset16Active
			MAX-ACCESS read-only
			STATUS current
			DESCRIPTION
				"Shows the active preset"
		::= { utg2000c01v1Entry 3 }

		-- 1.3.6.1.4.1.10106.3.101291.1.1.5
		utg2000c01v1LoadPreset OBJECT-TYPE
			SYNTAX Preset16Load
			MAX-ACCESS read-write
			STATUS current
			DESCRIPTION
				"Allows loading a preset"
		::= { utg2000c01v1Entry 5 }

		-- 1.3.6.1.4.1.10106.3.101291.1.1.7
		utg2000c01v1SavePreset OBJECT-TYPE
			SYNTAX Preset16Save
			MAX-ACCESS read-write
			STATUS current
			DESCRIPTION
				"Allows saving a preset"
		::= { utg2000c01v1Entry 7 }

		-- 1.3.6.1.4.1.10106.3.101291.1.1.9
		utg2000c01v1SdiRefInput OBJECT-TYPE
			SYNTAX Bit0Opt1Ele
			MAX-ACCESS read-write
			STATUS current
			DESCRIPTION
				"Allows selecting the input used for digital reference"
		::= { utg2000c01v1Entry 9 }

		-- 1.3.6.1.4.1.10106.3.101291.1.1.11
		utg2000c01v1OutputFormat OBJECT-TYPE
			SYNTAX SdiHd12gFmt2
			MAX-ACCESS read-write
			STATUS current
			DESCRIPTION
				"Allows selecting the output format"
		::= { utg2000c01v1Entry 11 }

		-- 1.3.6.1.4.1.10106.3.101291.1.1.13
		utg2000c01v1Pattern OBJECT-TYPE
			SYNTAX Uint6
			MAX-ACCESS read-write
			STATUS current
			DESCRIPTION
				"Allows selecting the generated video signal pattern"
		::= { utg2000c01v1Entry 13 }

		-- 1.3.6.1.4.1.10106.3.101291.1.1.15
		utg2000c01v1RstErrors OBJECT-TYPE
			SYNTAX BitMask
			MAX-ACCESS read-write
			STATUS current
			DESCRIPTION
				"Clear the errors"
		::= { utg2000c01v1Entry 15 }

		-- 1.3.6.1.4.1.10106.3.101291.1.1.17
		utg2000c01v1ExpRefFormat OBJECT-TYPE
			SYNTAX SdiHd12gFmt2
			MAX-ACCESS read-write
			STATUS current
			DESCRIPTION
				"Allows selecting the expected format of the reference"
		::= { utg2000c01v1Entry 17 }

		-- 1.3.6.1.4.1.10106.3.101291.1.1.18
		utg2000c01v1ExpRefFormatTrapEnable OBJECT-TYPE
			SYNTAX AlarmEnable
			MAX-ACCESS read-write
			STATUS current
			DESCRIPTION
				"Allows selecting the expected format of the reference Trap Enable"
		::= { utg2000c01v1Entry 18 }

		-- 1.3.6.1.4.1.10106.3.101291.1.1.19
		utg2000c01v1RefInput OBJECT-TYPE
			SYNTAX RefSel1
			MAX-ACCESS read-write
			STATUS current
			DESCRIPTION
				"Allows selecting the reference input"
		::= { utg2000c01v1Entry 19 }

		-- 1.3.6.1.4.1.10106.3.101291.1.1.20
		utg2000c01v1RefInputTrapEnable OBJECT-TYPE
			SYNTAX AlarmEnable
			MAX-ACCESS read-write
			STATUS current
			DESCRIPTION
				"Allows selecting the reference input Trap Enable"
		::= { utg2000c01v1Entry 20 }

		-- 1.3.6.1.4.1.10106.3.101291.1.1.21
		utg2000c01v1MeasInput OBJECT-TYPE
			SYNTAX RefSel1
			MAX-ACCESS read-write
			STATUS current
			DESCRIPTION
				"Allows selecting the input used for delay mesaurement"
		::= { utg2000c01v1Entry 21 }

		-- 1.3.6.1.4.1.10106.3.101291.1.1.23
		utg2000c01v1HDelay OBJECT-TYPE
			SYNTAX DelayPixel4
			MAX-ACCESS read-write
			STATUS current
			DESCRIPTION
				"Allows adjusting the video horizontal delay of main output"
		::= { utg2000c01v1Entry 23 }

		-- 1.3.6.1.4.1.10106.3.101291.1.1.25
		utg2000c01v1VDelay OBJECT-TYPE
			SYNTAX DelayLines3
			MAX-ACCESS read-write
			STATUS current
			DESCRIPTION
				"Allows adjusting the video vertical delay of main output"
		::= { utg2000c01v1Entry 25 }

		-- 1.3.6.1.4.1.10106.3.101291.1.1.27
		utg2000c01v1AvDlyBlack OBJECT-TYPE
			SYNTAX LumaUint8
			MAX-ACCESS read-write
			STATUS current
			DESCRIPTION
				"Maximum luminance value accepted for black frame detection"
		::= { utg2000c01v1Entry 27 }

		-- 1.3.6.1.4.1.10106.3.101291.1.1.29
		utg2000c01v1AvDlySil OBJECT-TYPE
			SYNTAX LevelDbfs2x
			MAX-ACCESS read-write
			STATUS current
			DESCRIPTION
				"Maximum audio level accepted for silence detection"
		::= { utg2000c01v1Entry 29 }

		-- 1.3.6.1.4.1.10106.3.101291.1.1.31
		utg2000c01v1OsdDlyEn OBJECT-TYPE
			SYNTAX Bit0No1Yes
			MAX-ACCESS read-write
			STATUS current
			DESCRIPTION
				"Shows A/V delays instead of the specified texts"
		::= { utg2000c01v1Entry 31 }

		-- 1.3.6.1.4.1.10106.3.101291.1.1.33
		utg2000c01v1Pwm OBJECT-TYPE
			SYNTAX Uint8X
			MAX-ACCESS read-write
			STATUS current
			DESCRIPTION
				"Allows adjusting the internal TCXO"
		::= { utg2000c01v1Entry 33 }

		-- 1.3.6.1.4.1.10106.3.101291.1.1.35
		utg2000c01v1OverlayIo1 OBJECT-TYPE
			SYNTAX Bit0No1Yes
			MAX-ACCESS read-write
			STATUS current
			DESCRIPTION
				"Enables overlay on SDI video output I/O1"
		::= { utg2000c01v1Entry 35 }

		-- 1.3.6.1.4.1.10106.3.101291.1.1.37
		utg2000c01v1OverlayIo2 OBJECT-TYPE
			SYNTAX Bit0No1Yes
			MAX-ACCESS read-write
			STATUS current
			DESCRIPTION
				"Enables overlay on SDI video output I/O2"
		::= { utg2000c01v1Entry 37 }

		-- 1.3.6.1.4.1.10106.3.101291.1.1.39
		utg2000c01v1OverlayIo3 OBJECT-TYPE
			SYNTAX Bit0No1Yes
			MAX-ACCESS read-write
			STATUS current
			DESCRIPTION
				"Enables overlay on SDI video output I/O3"
		::= { utg2000c01v1Entry 39 }

		-- 1.3.6.1.4.1.10106.3.101291.1.1.41
		utg2000c01v1OverlayIo4 OBJECT-TYPE
			SYNTAX Bit0No1Yes
			MAX-ACCESS read-write
			STATUS current
			DESCRIPTION
				"Enables overlay on SDI video output I/O4"
		::= { utg2000c01v1Entry 41 }

		-- 1.3.6.1.4.1.10106.3.101291.1.1.43
		utg2000c01v1OverlayOptout OBJECT-TYPE
			SYNTAX Bit0No1Yes
			MAX-ACCESS read-write
			STATUS current
			DESCRIPTION
				"Enables overlay on SDI video output OPT. OUT"
		::= { utg2000c01v1Entry 43 }

		-- 1.3.6.1.4.1.10106.3.101291.1.1.45
		utg2000c01v1EnLogo11 OBJECT-TYPE
			SYNTAX Bit0No1Yes
			MAX-ACCESS read-write
			STATUS current
			DESCRIPTION
				"Show logo 1"
		::= { utg2000c01v1Entry 45 }

		-- 1.3.6.1.4.1.10106.3.101291.1.1.47
		utg2000c01v1IdLogo11 OBJECT-TYPE
			SYNTAX Uint8
			MAX-ACCESS read-write
			STATUS current
			DESCRIPTION
				"Logo 1 ID"
		::= { utg2000c01v1Entry 47 }

		-- 1.3.6.1.4.1.10106.3.101291.1.1.49
		utg2000c01v1XoffLogo11 OBJECT-TYPE
			SYNTAX DelayPixel4
			MAX-ACCESS read-write
			STATUS current
			DESCRIPTION
				"Logo 1 X offset"
		::= { utg2000c01v1Entry 49 }

		-- 1.3.6.1.4.1.10106.3.101291.1.1.51
		utg2000c01v1YoffLogo11 OBJECT-TYPE
			SYNTAX DelayLines3
			MAX-ACCESS read-write
			STATUS current
			DESCRIPTION
				"Logo 1 Y offset"
		::= { utg2000c01v1Entry 51 }

		-- 1.3.6.1.4.1.10106.3.101291.1.1.53
		utg2000c01v1EnLogo21 OBJECT-TYPE
			SYNTAX Bit0No1Yes
			MAX-ACCESS read-write
			STATUS current
			DESCRIPTION
				"Show logo 2"
		::= { utg2000c01v1Entry 53 }

		-- 1.3.6.1.4.1.10106.3.101291.1.1.55
		utg2000c01v1IdLogo21 OBJECT-TYPE
			SYNTAX Uint8
			MAX-ACCESS read-write
			STATUS current
			DESCRIPTION
				"Logo 2 ID"
		::= { utg2000c01v1Entry 55 }

		-- 1.3.6.1.4.1.10106.3.101291.1.1.57
		utg2000c01v1XoffLogo21 OBJECT-TYPE
			SYNTAX DelayPixel4
			MAX-ACCESS read-write
			STATUS current
			DESCRIPTION
				"Logo 2 X offset"
		::= { utg2000c01v1Entry 57 }

		-- 1.3.6.1.4.1.10106.3.101291.1.1.59
		utg2000c01v1YoffLogo21 OBJECT-TYPE
			SYNTAX DelayLines3
			MAX-ACCESS read-write
			STATUS current
			DESCRIPTION
				"Logo 2 Y offset"
		::= { utg2000c01v1Entry 59 }

		-- 1.3.6.1.4.1.10106.3.101291.1.1.61
		utg2000c01v1EnOsd1 OBJECT-TYPE
			SYNTAX Bit0No1Yes
			MAX-ACCESS read-write
			STATUS current
			DESCRIPTION
				"Show OSD 1"
		::= { utg2000c01v1Entry 61 }

		-- 1.3.6.1.4.1.10106.3.101291.1.1.63
		utg2000c01v1Osd1Size OBJECT-TYPE
			SYNTAX Size3
			MAX-ACCESS read-write
			STATUS current
			DESCRIPTION
				"OSD size adjustment"
		::= { utg2000c01v1Entry 63 }

		-- 1.3.6.1.4.1.10106.3.101291.1.1.65
		utg2000c01v1EnOsd2 OBJECT-TYPE
			SYNTAX Bit0No1Yes
			MAX-ACCESS read-write
			STATUS current
			DESCRIPTION
				"Show OSD 2"
		::= { utg2000c01v1Entry 65 }

		-- 1.3.6.1.4.1.10106.3.101291.1.1.67
		utg2000c01v1Osd2Size OBJECT-TYPE
			SYNTAX Size3
			MAX-ACCESS read-write
			STATUS current
			DESCRIPTION
				"OSD size adjustment"
		::= { utg2000c01v1Entry 67 }

		-- 1.3.6.1.4.1.10106.3.101291.1.1.69
		utg2000c01v1Osd1MovEna OBJECT-TYPE
			SYNTAX Bit0No1Yes
			MAX-ACCESS read-write
			STATUS current
			DESCRIPTION
				"OSD movement enable"
		::= { utg2000c01v1Entry 69 }

		-- 1.3.6.1.4.1.10106.3.101291.1.1.71
		utg2000c01v1Osd1SpeedH OBJECT-TYPE
			SYNTAX Uint4
			MAX-ACCESS read-write
			STATUS current
			DESCRIPTION
				"OSD speed h"
		::= { utg2000c01v1Entry 71 }

		-- 1.3.6.1.4.1.10106.3.101291.1.1.73
		utg2000c01v1Osd1SpeedV OBJECT-TYPE
			SYNTAX Uint4
			MAX-ACCESS read-write
			STATUS current
			DESCRIPTION
				"OSD speed v"
		::= { utg2000c01v1Entry 73 }

		-- 1.3.6.1.4.1.10106.3.101291.1.1.75
		utg2000c01v1Osd1StartH OBJECT-TYPE
			SYNTAX DelayPixel5
			MAX-ACCESS read-write
			STATUS current
			DESCRIPTION
				"OSD start pixel h"
		::= { utg2000c01v1Entry 75 }

		-- 1.3.6.1.4.1.10106.3.101291.1.1.77
		utg2000c01v1Osd1StartV OBJECT-TYPE
			SYNTAX DelayLines3
			MAX-ACCESS read-write
			STATUS current
			DESCRIPTION
				"OSD start pixel v"
		::= { utg2000c01v1Entry 77 }

		-- 1.3.6.1.4.1.10106.3.101291.1.1.79
		utg2000c01v1Osd1EndH OBJECT-TYPE
			SYNTAX DelayPixel5
			MAX-ACCESS read-write
			STATUS current
			DESCRIPTION
				"OSD end pixel h"
		::= { utg2000c01v1Entry 79 }

		-- 1.3.6.1.4.1.10106.3.101291.1.1.81
		utg2000c01v1Osd1EndV OBJECT-TYPE
			SYNTAX DelayLines3
			MAX-ACCESS read-write
			STATUS current
			DESCRIPTION
				"OSD end pixel v"
		::= { utg2000c01v1Entry 81 }

		-- 1.3.6.1.4.1.10106.3.101291.1.1.83
		utg2000c01v1EnAudIm1 OBJECT-TYPE
			SYNTAX Bit0No1Yes
			MAX-ACCESS read-write
			STATUS current
			DESCRIPTION
				"Enable audio in image/sub-image 1"
		::= { utg2000c01v1Entry 83 }

		-- 1.3.6.1.4.1.10106.3.101291.1.1.85
		utg2000c01v1EnAudIm2 OBJECT-TYPE
			SYNTAX Bit0No1Yes
			MAX-ACCESS read-write
			STATUS current
			DESCRIPTION
				"Enable audio in sub- image 2"
		::= { utg2000c01v1Entry 85 }

		-- 1.3.6.1.4.1.10106.3.101291.1.1.87
		utg2000c01v1EnAudIm3 OBJECT-TYPE
			SYNTAX Bit0No1Yes
			MAX-ACCESS read-write
			STATUS current
			DESCRIPTION
				"Enable audio in sub- image 3"
		::= { utg2000c01v1Entry 87 }

		-- 1.3.6.1.4.1.10106.3.101291.1.1.89
		utg2000c01v1EnAudIm4 OBJECT-TYPE
			SYNTAX Bit0No1Yes
			MAX-ACCESS read-write
			STATUS current
			DESCRIPTION
				"Enable audio in sub-image 4"
		::= { utg2000c01v1Entry 89 }

		-- 1.3.6.1.4.1.10106.3.101291.1.1.91
		utg2000c01v1EnGrp1Aud0 OBJECT-TYPE
			SYNTAX Bit0No1Yes
			MAX-ACCESS read-write
			STATUS current
			DESCRIPTION
				"Allows inserting group 1 audio packets"
		::= { utg2000c01v1Entry 91 }

		-- 1.3.6.1.4.1.10106.3.101291.1.1.93
		utg2000c01v1EnGrp2Aud0 OBJECT-TYPE
			SYNTAX Bit0No1Yes
			MAX-ACCESS read-write
			STATUS current
			DESCRIPTION
				"Allows inserting group 2 audio packets"
		::= { utg2000c01v1Entry 93 }

		-- 1.3.6.1.4.1.10106.3.101291.1.1.95
		utg2000c01v1EnGrp3Aud0 OBJECT-TYPE
			SYNTAX Bit0No1Yes
			MAX-ACCESS read-write
			STATUS current
			DESCRIPTION
				"Allows inserting group 3 audio packets"
		::= { utg2000c01v1Entry 95 }

		-- 1.3.6.1.4.1.10106.3.101291.1.1.97
		utg2000c01v1EnGrp4Aud0 OBJECT-TYPE
			SYNTAX Bit0No1Yes
			MAX-ACCESS read-write
			STATUS current
			DESCRIPTION
				"Allows inserting group 4 audio packets"
		::= { utg2000c01v1Entry 97 }

		-- 1.3.6.1.4.1.10106.3.101291.1.1.99
		utg2000c01v1VidDip0 OBJECT-TYPE
			SYNTAX Bit0No1Yes
			MAX-ACCESS read-write
			STATUS current
			DESCRIPTION
				"Black in audio ID silences"
		::= { utg2000c01v1Entry 99 }

		-- 1.3.6.1.4.1.10106.3.101291.1.1.101
		utg2000c01v1AudFrP0G00 OBJECT-TYPE
			SYNTAX AudioFreq1
			MAX-ACCESS read-write
			STATUS current
			DESCRIPTION
				"Allows selecting the audio signal in pair 0 group 1"
		::= { utg2000c01v1Entry 101 }

		-- 1.3.6.1.4.1.10106.3.101291.1.1.103
		utg2000c01v1AudFrP1G00 OBJECT-TYPE
			SYNTAX AudioFreq1
			MAX-ACCESS read-write
			STATUS current
			DESCRIPTION
				"Allows selecting the audio signal in pair 1 group 1"
		::= { utg2000c01v1Entry 103 }

		-- 1.3.6.1.4.1.10106.3.101291.1.1.105
		utg2000c01v1AudFrP0G10 OBJECT-TYPE
			SYNTAX AudioFreq1
			MAX-ACCESS read-write
			STATUS current
			DESCRIPTION
				"Allows selecting the audio signal in pair 0 group 2"
		::= { utg2000c01v1Entry 105 }

		-- 1.3.6.1.4.1.10106.3.101291.1.1.107
		utg2000c01v1AudFrP1G10 OBJECT-TYPE
			SYNTAX AudioFreq1
			MAX-ACCESS read-write
			STATUS current
			DESCRIPTION
				"Allows selecting the audio signal in pair 1 group 2"
		::= { utg2000c01v1Entry 107 }

		-- 1.3.6.1.4.1.10106.3.101291.1.1.109
		utg2000c01v1AudFrP0G20 OBJECT-TYPE
			SYNTAX AudioFreq1
			MAX-ACCESS read-write
			STATUS current
			DESCRIPTION
				"Allows selecting the audio signal in pair 0 group 3"
		::= { utg2000c01v1Entry 109 }

		-- 1.3.6.1.4.1.10106.3.101291.1.1.111
		utg2000c01v1AudFrP1G20 OBJECT-TYPE
			SYNTAX AudioFreq1
			MAX-ACCESS read-write
			STATUS current
			DESCRIPTION
				"Allows selecting the audio signal in pair 1 group 3"
		::= { utg2000c01v1Entry 111 }

		-- 1.3.6.1.4.1.10106.3.101291.1.1.113
		utg2000c01v1AudFrP0G30 OBJECT-TYPE
			SYNTAX AudioFreq1
			MAX-ACCESS read-write
			STATUS current
			DESCRIPTION
				"Allows selecting the audio signal in pair 0 group 4"
		::= { utg2000c01v1Entry 113 }

		-- 1.3.6.1.4.1.10106.3.101291.1.1.115
		utg2000c01v1AudFrP1G30 OBJECT-TYPE
			SYNTAX AudioFreq1
			MAX-ACCESS read-write
			STATUS current
			DESCRIPTION
				"Allows selecting the audio signal in pair 1 group 4"
		::= { utg2000c01v1Entry 115 }

		-- 1.3.6.1.4.1.10106.3.101291.1.1.117
		utg2000c01v1AudDipP0G00 OBJECT-TYPE
			SYNTAX Bit0Dis1Ena
			MAX-ACCESS read-write
			STATUS current
			DESCRIPTION
				"Allows enabling the insertion of silences for channel identification in pair 0 group 1"
		::= { utg2000c01v1Entry 117 }

		-- 1.3.6.1.4.1.10106.3.101291.1.1.119
		utg2000c01v1AudDipP1G00 OBJECT-TYPE
			SYNTAX Bit0Dis1Ena
			MAX-ACCESS read-write
			STATUS current
			DESCRIPTION
				"Allows enabling the insertion of silences for channel identification in pair 1 group 1"
		::= { utg2000c01v1Entry 119 }

		-- 1.3.6.1.4.1.10106.3.101291.1.1.121
		utg2000c01v1AudDipP0G10 OBJECT-TYPE
			SYNTAX Bit0Dis1Ena
			MAX-ACCESS read-write
			STATUS current
			DESCRIPTION
				"Allows enabling the insertion of silences for channel identification in pair 0 group 2"
		::= { utg2000c01v1Entry 121 }

		-- 1.3.6.1.4.1.10106.3.101291.1.1.123
		utg2000c01v1AudDipP1G10 OBJECT-TYPE
			SYNTAX Bit0Dis1Ena
			MAX-ACCESS read-write
			STATUS current
			DESCRIPTION
				"Allows enabling the insertion of silences for channel identification in pair 1 group 2"
		::= { utg2000c01v1Entry 123 }

		-- 1.3.6.1.4.1.10106.3.101291.1.1.125
		utg2000c01v1AudDipP0G20 OBJECT-TYPE
			SYNTAX Bit0Dis1Ena
			MAX-ACCESS read-write
			STATUS current
			DESCRIPTION
				"Allows enabling the insertion of silences for channel identification in pair 0 group 3"
		::= { utg2000c01v1Entry 125 }

		-- 1.3.6.1.4.1.10106.3.101291.1.1.127
		utg2000c01v1AudDipP1G20 OBJECT-TYPE
			SYNTAX Bit0Dis1Ena
			MAX-ACCESS read-write
			STATUS current
			DESCRIPTION
				"Allows enabling the insertion of silences for channel identification in pair 1 group 3"
		::= { utg2000c01v1Entry 127 }

		-- 1.3.6.1.4.1.10106.3.101291.1.1.129
		utg2000c01v1AudDipP0G30 OBJECT-TYPE
			SYNTAX Bit0Dis1Ena
			MAX-ACCESS read-write
			STATUS current
			DESCRIPTION
				"Allows enabling the insertion of silences for channel identification in pair 0 group 4"
		::= { utg2000c01v1Entry 129 }

		-- 1.3.6.1.4.1.10106.3.101291.1.1.131
		utg2000c01v1AudDipP1G30 OBJECT-TYPE
			SYNTAX Bit0Dis1Ena
			MAX-ACCESS read-write
			STATUS current
			DESCRIPTION
				"Allows enabling the insertion of silences for channel identification in pair 1 group 4"
		::= { utg2000c01v1Entry 131 }

		-- 1.3.6.1.4.1.10106.3.101291.1.1.133
		utg2000c01v1AudLevP0G00 OBJECT-TYPE
			SYNTAX AudioLev0
			MAX-ACCESS read-write
			STATUS current
			DESCRIPTION
				"Allows selecting the audio level in pair 0 group 1"
		::= { utg2000c01v1Entry 133 }

		-- 1.3.6.1.4.1.10106.3.101291.1.1.135
		utg2000c01v1AudLevP0G10 OBJECT-TYPE
			SYNTAX AudioLev0
			MAX-ACCESS read-write
			STATUS current
			DESCRIPTION
				"Allows selecting the audio level in pair 1 group 1"
		::= { utg2000c01v1Entry 135 }

		-- 1.3.6.1.4.1.10106.3.101291.1.1.137
		utg2000c01v1AudLevP1G00 OBJECT-TYPE
			SYNTAX AudioLev0
			MAX-ACCESS read-write
			STATUS current
			DESCRIPTION
				"Allows selecting the audio level in pair 0 group 2"
		::= { utg2000c01v1Entry 137 }

		-- 1.3.6.1.4.1.10106.3.101291.1.1.139
		utg2000c01v1AudLevP1G10 OBJECT-TYPE
			SYNTAX AudioLev0
			MAX-ACCESS read-write
			STATUS current
			DESCRIPTION
				"Allows selecting the audio level in pair 1 group 2"
		::= { utg2000c01v1Entry 139 }

		-- 1.3.6.1.4.1.10106.3.101291.1.1.141
		utg2000c01v1AudLevP0G20 OBJECT-TYPE
			SYNTAX AudioLev0
			MAX-ACCESS read-write
			STATUS current
			DESCRIPTION
				"Allows selecting the audio level in pair 0 group 3"
		::= { utg2000c01v1Entry 141 }

		-- 1.3.6.1.4.1.10106.3.101291.1.1.143
		utg2000c01v1AudLevP1G20 OBJECT-TYPE
			SYNTAX AudioLev0
			MAX-ACCESS read-write
			STATUS current
			DESCRIPTION
				"Allows selecting the audio level in pair 1 group 3"
		::= { utg2000c01v1Entry 143 }

		-- 1.3.6.1.4.1.10106.3.101291.1.1.145
		utg2000c01v1AudLevP0G30 OBJECT-TYPE
			SYNTAX AudioLev0
			MAX-ACCESS read-write
			STATUS current
			DESCRIPTION
				"Allows selecting the audio level in pair 0 group 4"
		::= { utg2000c01v1Entry 145 }

		-- 1.3.6.1.4.1.10106.3.101291.1.1.147
		utg2000c01v1AudLevP1G30 OBJECT-TYPE
			SYNTAX AudioLev0
			MAX-ACCESS read-write
			STATUS current
			DESCRIPTION
				"Allows selecting the audio level in pair 1 group 4"
		::= { utg2000c01v1Entry 147 }

		-- 1.3.6.1.4.1.10106.3.101291.1.1.149
		utg2000c01v1DropFrame OBJECT-TYPE
			SYNTAX BitMask
			MAX-ACCESS read-write
			STATUS current
			DESCRIPTION
				"Enables time compensated mode in 59.94 Hz formats"
		::= { utg2000c01v1Entry 149 }

		-- 1.3.6.1.4.1.10106.3.101291.1.1.151
		utg2000c01v1Bgf OBJECT-TYPE
			SYNTAX BgfBits
			MAX-ACCESS read-write
			STATUS current
			DESCRIPTION
				"Contents of the binary group flags in the time code"
		::= { utg2000c01v1Entry 151 }

		-- 1.3.6.1.4.1.10106.3.101291.1.1.153
		utg2000c01v1DateFormat OBJECT-TYPE
			SYNTAX DateFmt
			MAX-ACCESS read-write
			STATUS current
			DESCRIPTION
				"Selects date format in the BGF (binary group flags)"
		::= { utg2000c01v1Entry 153 }

		-- 1.3.6.1.4.1.10106.3.101291.1.1.155
		utg2000c01v1EnDateGen OBJECT-TYPE
			SYNTAX BitMask
			MAX-ACCESS read-write
			STATUS current
			DESCRIPTION
				"Enables date insertion in time code"
		::= { utg2000c01v1Entry 155 }

		-- 1.3.6.1.4.1.10106.3.101291.1.1.157
		utg2000c01v1AdjHourDay OBJECT-TYPE
			SYNTAX Uint5
			MAX-ACCESS read-write
			STATUS current
			DESCRIPTION
				"Resets time code frame counter value at the end of this UTC hour (59.94 Hz formats only)"
		::= { utg2000c01v1Entry 157 }

		-- 1.3.6.1.4.1.10106.3.101291.1.1.159
		utg2000c01v1SumMonthSt OBJECT-TYPE
			SYNTAX Month
			MAX-ACCESS read-write
			STATUS current
			DESCRIPTION
				"It allows selecting the month when summer time starts"
		::= { utg2000c01v1Entry 159 }

		-- 1.3.6.1.4.1.10106.3.101291.1.1.161
		utg2000c01v1SumWeekSt OBJECT-TYPE
			SYNTAX WeekOfMonth
			MAX-ACCESS read-write
			STATUS current
			DESCRIPTION
				"It allows selecting the week of the month when summer time starts"
		::= { utg2000c01v1Entry 161 }

		-- 1.3.6.1.4.1.10106.3.101291.1.1.163
		utg2000c01v1SumWDaySt OBJECT-TYPE
			SYNTAX Day
			MAX-ACCESS read-write
			STATUS current
			DESCRIPTION
				"It allows selecting the week day when summer time starts"
		::= { utg2000c01v1Entry 163 }

		-- 1.3.6.1.4.1.10106.3.101291.1.1.165
		utg2000c01v1SumHourSt OBJECT-TYPE
			SYNTAX TimeH1
			MAX-ACCESS read-write
			STATUS current
			DESCRIPTION
				"It allows selecting the UTC hour when summer time starts"
		::= { utg2000c01v1Entry 165 }

		-- 1.3.6.1.4.1.10106.3.101291.1.1.167
		utg2000c01v1SumHourOffset OBJECT-TYPE
			SYNTAX Int8
			MAX-ACCESS read-write
			STATUS current
			DESCRIPTION
				"It allows selecting the local time offset at summer time"
		::= { utg2000c01v1Entry 167 }

		-- 1.3.6.1.4.1.10106.3.101291.1.1.169
		utg2000c01v1WinMonthSt OBJECT-TYPE
			SYNTAX Month
			MAX-ACCESS read-write
			STATUS current
			DESCRIPTION
				"It allows selecting the month when winter time starts"
		::= { utg2000c01v1Entry 169 }

		-- 1.3.6.1.4.1.10106.3.101291.1.1.171
		utg2000c01v1WinWeekSt OBJECT-TYPE
			SYNTAX WeekOfMonth
			MAX-ACCESS read-write
			STATUS current
			DESCRIPTION
				"It allows selecting the week of the month when winter time starts"
		::= { utg2000c01v1Entry 171 }

		-- 1.3.6.1.4.1.10106.3.101291.1.1.173
		utg2000c01v1WinWDaySt OBJECT-TYPE
			SYNTAX Day
			MAX-ACCESS read-write
			STATUS current
			DESCRIPTION
				"It allows selecting the week day when winter time starts"
		::= { utg2000c01v1Entry 173 }

		-- 1.3.6.1.4.1.10106.3.101291.1.1.175
		utg2000c01v1WinHourSt OBJECT-TYPE
			SYNTAX TimeH1
			MAX-ACCESS read-write
			STATUS current
			DESCRIPTION
				"It allows selecting the UTC hour when winter time starts"
		::= { utg2000c01v1Entry 175 }

		-- 1.3.6.1.4.1.10106.3.101291.1.1.177
		utg2000c01v1WinHourOffset OBJECT-TYPE
			SYNTAX Int8
			MAX-ACCESS read-write
			STATUS current
			DESCRIPTION
				"It allows selecting the local time offset at winter time"
		::= { utg2000c01v1Entry 177 }

		-- 1.3.6.1.4.1.10106.3.101291.1.1.179
		utg2000c01v1EnDlsave OBJECT-TYPE
			SYNTAX BitMask
			MAX-ACCESS read-write
			STATUS current
			DESCRIPTION
				"It allows enabling automatic daylight saving"
		::= { utg2000c01v1Entry 179 }

		-- 1.3.6.1.4.1.10106.3.101291.1.1.181
		utg2000c01v1Delay1G1p0l OBJECT-TYPE
			SYNTAX DelayX1Ms
			MAX-ACCESS read-only
			STATUS current
			DESCRIPTION
				"A negative value implies that audio is advanced with respect to video"
		::= { utg2000c01v1Entry 181 }

		-- 1.3.6.1.4.1.10106.3.101291.1.1.183
		utg2000c01v1Delay1G1p0r OBJECT-TYPE
			SYNTAX DelayX1Ms
			MAX-ACCESS read-only
			STATUS current
			DESCRIPTION
				"A negative value implies that audio is advanced with respect to video"
		::= { utg2000c01v1Entry 183 }

		-- 1.3.6.1.4.1.10106.3.101291.1.1.185
		utg2000c01v1Delay1G1p1l OBJECT-TYPE
			SYNTAX DelayX1Ms
			MAX-ACCESS read-only
			STATUS current
			DESCRIPTION
				"A negative value implies that audio is advanced with respect to video"
		::= { utg2000c01v1Entry 185 }

		-- 1.3.6.1.4.1.10106.3.101291.1.1.187
		utg2000c01v1Delay1G1p1r OBJECT-TYPE
			SYNTAX DelayX1Ms
			MAX-ACCESS read-only
			STATUS current
			DESCRIPTION
				"A negative value implies that audio is advanced with respect to video"
		::= { utg2000c01v1Entry 187 }

		-- 1.3.6.1.4.1.10106.3.101291.1.1.189
		utg2000c01v1Delay1G2p0l OBJECT-TYPE
			SYNTAX DelayX1Ms
			MAX-ACCESS read-only
			STATUS current
			DESCRIPTION
				"A negative value implies that audio is advanced with respect to video"
		::= { utg2000c01v1Entry 189 }

		-- 1.3.6.1.4.1.10106.3.101291.1.1.191
		utg2000c01v1Delay1G2p0r OBJECT-TYPE
			SYNTAX DelayX1Ms
			MAX-ACCESS read-only
			STATUS current
			DESCRIPTION
				"A negative value implies that audio is advanced with respect to video"
		::= { utg2000c01v1Entry 191 }

		-- 1.3.6.1.4.1.10106.3.101291.1.1.193
		utg2000c01v1Delay1G2p1l OBJECT-TYPE
			SYNTAX DelayX1Ms
			MAX-ACCESS read-only
			STATUS current
			DESCRIPTION
				"A negative value implies that audio is advanced with respect to video"
		::= { utg2000c01v1Entry 193 }

		-- 1.3.6.1.4.1.10106.3.101291.1.1.195
		utg2000c01v1Delay1G2p1r OBJECT-TYPE
			SYNTAX DelayX1Ms
			MAX-ACCESS read-only
			STATUS current
			DESCRIPTION
				"A negative value implies that audio is advanced with respect to video"
		::= { utg2000c01v1Entry 195 }

		-- 1.3.6.1.4.1.10106.3.101291.1.1.197
		utg2000c01v1Delay1G3p0l OBJECT-TYPE
			SYNTAX DelayX1Ms
			MAX-ACCESS read-only
			STATUS current
			DESCRIPTION
				"A negative value implies that audio is advanced with respect to video"
		::= { utg2000c01v1Entry 197 }

		-- 1.3.6.1.4.1.10106.3.101291.1.1.199
		utg2000c01v1Delay1G3p0r OBJECT-TYPE
			SYNTAX DelayX1Ms
			MAX-ACCESS read-only
			STATUS current
			DESCRIPTION
				"A negative value implies that audio is advanced with respect to video"
		::= { utg2000c01v1Entry 199 }

		-- 1.3.6.1.4.1.10106.3.101291.1.1.201
		utg2000c01v1Delay1G3p1l OBJECT-TYPE
			SYNTAX DelayX1Ms
			MAX-ACCESS read-only
			STATUS current
			DESCRIPTION
				"A negative value implies that audio is advanced with respect to video"
		::= { utg2000c01v1Entry 201 }

		-- 1.3.6.1.4.1.10106.3.101291.1.1.203
		utg2000c01v1Delay1G3p1r OBJECT-TYPE
			SYNTAX DelayX1Ms
			MAX-ACCESS read-only
			STATUS current
			DESCRIPTION
				"A negative value implies that audio is advanced with respect to video"
		::= { utg2000c01v1Entry 203 }

		-- 1.3.6.1.4.1.10106.3.101291.1.1.205
		utg2000c01v1Delay1G4p0l OBJECT-TYPE
			SYNTAX DelayX1Ms
			MAX-ACCESS read-only
			STATUS current
			DESCRIPTION
				"A negative value implies that audio is advanced with respect to video"
		::= { utg2000c01v1Entry 205 }

		-- 1.3.6.1.4.1.10106.3.101291.1.1.207
		utg2000c01v1Delay1G4p0r OBJECT-TYPE
			SYNTAX DelayX1Ms
			MAX-ACCESS read-only
			STATUS current
			DESCRIPTION
				"A negative value implies that audio is advanced with respect to video"
		::= { utg2000c01v1Entry 207 }

		-- 1.3.6.1.4.1.10106.3.101291.1.1.209
		utg2000c01v1Delay1G4p1l OBJECT-TYPE
			SYNTAX DelayX1Ms
			MAX-ACCESS read-only
			STATUS current
			DESCRIPTION
				"A negative value implies that audio is advanced with respect to video"
		::= { utg2000c01v1Entry 209 }

		-- 1.3.6.1.4.1.10106.3.101291.1.1.211
		utg2000c01v1Delay1G4p1r OBJECT-TYPE
			SYNTAX DelayX1Ms
			MAX-ACCESS read-only
			STATUS current
			DESCRIPTION
				"A negative value implies that audio is advanced with respect to video"
		::= { utg2000c01v1Entry 211 }

		-- 1.3.6.1.4.1.10106.3.101291.1.1.213
		utg2000c01v1Av1SeqG1p0 OBJECT-TYPE
			SYNTAX BitFail
			MAX-ACCESS read-only
			STATUS current
			DESCRIPTION
				"The A/V delay measurement sequence was not correctly detected for this pair"
		::= { utg2000c01v1Entry 213 }

		-- 1.3.6.1.4.1.10106.3.101291.1.1.215
		utg2000c01v1Av1SeqG1p1 OBJECT-TYPE
			SYNTAX BitFail
			MAX-ACCESS read-only
			STATUS current
			DESCRIPTION
				"The A/V delay measurement sequence was not correctly detected for this pair"
		::= { utg2000c01v1Entry 215 }

		-- 1.3.6.1.4.1.10106.3.101291.1.1.217
		utg2000c01v1Av1SeqG2p0 OBJECT-TYPE
			SYNTAX BitFail
			MAX-ACCESS read-only
			STATUS current
			DESCRIPTION
				"The A/V delay measurement sequence was not correctly detected for this pair"
		::= { utg2000c01v1Entry 217 }

		-- 1.3.6.1.4.1.10106.3.101291.1.1.219
		utg2000c01v1Av1SeqG2p1 OBJECT-TYPE
			SYNTAX BitFail
			MAX-ACCESS read-only
			STATUS current
			DESCRIPTION
				"The A/V delay measurement sequence was not correctly detected for this pair"
		::= { utg2000c01v1Entry 219 }

		-- 1.3.6.1.4.1.10106.3.101291.1.1.221
		utg2000c01v1Av1SeqG3p0 OBJECT-TYPE
			SYNTAX BitFail
			MAX-ACCESS read-only
			STATUS current
			DESCRIPTION
				"The A/V delay measurement sequence was not correctly detected for this pair"
		::= { utg2000c01v1Entry 221 }

		-- 1.3.6.1.4.1.10106.3.101291.1.1.223
		utg2000c01v1Av1SeqG3p1 OBJECT-TYPE
			SYNTAX BitFail
			MAX-ACCESS read-only
			STATUS current
			DESCRIPTION
				"The A/V delay measurement sequence was not correctly detected for this pair"
		::= { utg2000c01v1Entry 223 }

		-- 1.3.6.1.4.1.10106.3.101291.1.1.225
		utg2000c01v1Av1SeqG4p0 OBJECT-TYPE
			SYNTAX BitFail
			MAX-ACCESS read-only
			STATUS current
			DESCRIPTION
				"The A/V delay measurement sequence was not correctly detected for this pair"
		::= { utg2000c01v1Entry 225 }

		-- 1.3.6.1.4.1.10106.3.101291.1.1.227
		utg2000c01v1Av1SeqG4p1 OBJECT-TYPE
			SYNTAX BitFail
			MAX-ACCESS read-only
			STATUS current
			DESCRIPTION
				"The A/V delay measurement sequence was not correctly detected for this pair"
		::= { utg2000c01v1Entry 227 }

		-- 1.3.6.1.4.1.10106.3.101291.1.1.229
		utg2000c01v1Aud1GrpPres1 OBJECT-TYPE
			SYNTAX BitFailN
			MAX-ACCESS read-only
			STATUS current
			DESCRIPTION
				"Group 1 present"
		::= { utg2000c01v1Entry 229 }

		-- 1.3.6.1.4.1.10106.3.101291.1.1.231
		utg2000c01v1Aud1GrpPres2 OBJECT-TYPE
			SYNTAX BitFailN
			MAX-ACCESS read-only
			STATUS current
			DESCRIPTION
				"Group 2 present"
		::= { utg2000c01v1Entry 231 }

		-- 1.3.6.1.4.1.10106.3.101291.1.1.233
		utg2000c01v1Aud1GrpPres3 OBJECT-TYPE
			SYNTAX BitFailN
			MAX-ACCESS read-only
			STATUS current
			DESCRIPTION
				"Group 3 present"
		::= { utg2000c01v1Entry 233 }

		-- 1.3.6.1.4.1.10106.3.101291.1.1.235
		utg2000c01v1Aud1GrpPres4 OBJECT-TYPE
			SYNTAX BitFailN
			MAX-ACCESS read-only
			STATUS current
			DESCRIPTION
				"Group 4 present"
		::= { utg2000c01v1Entry 235 }

		-- 1.3.6.1.4.1.10106.3.101291.1.1.237
		utg2000c01v1Av1SeqPhase OBJECT-TYPE
			SYNTAX Uint8
			MAX-ACCESS read-only
			STATUS current
			DESCRIPTION
				"Seconds remaining until next delay measurement sequence starts"
		::= { utg2000c01v1Entry 237 }

		-- 1.3.6.1.4.1.10106.3.101291.1.1.239
		utg2000c01v1Delay2G1p0l OBJECT-TYPE
			SYNTAX DelayX1Ms
			MAX-ACCESS read-only
			STATUS current
			DESCRIPTION
				"A negative value implies that audio is advanced with respect to video"
		::= { utg2000c01v1Entry 239 }

		-- 1.3.6.1.4.1.10106.3.101291.1.1.241
		utg2000c01v1Delay2G1p0r OBJECT-TYPE
			SYNTAX DelayX1Ms
			MAX-ACCESS read-only
			STATUS current
			DESCRIPTION
				"A negative value implies that audio is advanced with respect to video"
		::= { utg2000c01v1Entry 241 }

		-- 1.3.6.1.4.1.10106.3.101291.1.1.243
		utg2000c01v1Delay2G1p1l OBJECT-TYPE
			SYNTAX DelayX1Ms
			MAX-ACCESS read-only
			STATUS current
			DESCRIPTION
				"A negative value implies that audio is advanced with respect to video"
		::= { utg2000c01v1Entry 243 }

		-- 1.3.6.1.4.1.10106.3.101291.1.1.245
		utg2000c01v1Delay2G1p1r OBJECT-TYPE
			SYNTAX DelayX1Ms
			MAX-ACCESS read-only
			STATUS current
			DESCRIPTION
				"A negative value implies that audio is advanced with respect to video"
		::= { utg2000c01v1Entry 245 }

		-- 1.3.6.1.4.1.10106.3.101291.1.1.247
		utg2000c01v1Delay2G2p0l OBJECT-TYPE
			SYNTAX DelayX1Ms
			MAX-ACCESS read-only
			STATUS current
			DESCRIPTION
				"A negative value implies that audio is advanced with respect to video"
		::= { utg2000c01v1Entry 247 }

		-- 1.3.6.1.4.1.10106.3.101291.1.1.249
		utg2000c01v1Delay2G2p0r OBJECT-TYPE
			SYNTAX DelayX1Ms
			MAX-ACCESS read-only
			STATUS current
			DESCRIPTION
				"A negative value implies that audio is advanced with respect to video"
		::= { utg2000c01v1Entry 249 }

		-- 1.3.6.1.4.1.10106.3.101291.1.1.251
		utg2000c01v1Delay2G2p1l OBJECT-TYPE
			SYNTAX DelayX1Ms
			MAX-ACCESS read-only
			STATUS current
			DESCRIPTION
				"A negative value implies that audio is advanced with respect to video"
		::= { utg2000c01v1Entry 251 }

		-- 1.3.6.1.4.1.10106.3.101291.1.1.253
		utg2000c01v1Delay2G2p1r OBJECT-TYPE
			SYNTAX DelayX1Ms
			MAX-ACCESS read-only
			STATUS current
			DESCRIPTION
				"A negative value implies that audio is advanced with respect to video"
		::= { utg2000c01v1Entry 253 }

		-- 1.3.6.1.4.1.10106.3.101291.1.1.255
		utg2000c01v1Delay2G3p0l OBJECT-TYPE
			SYNTAX DelayX1Ms
			MAX-ACCESS read-only
			STATUS current
			DESCRIPTION
				"A negative value implies that audio is advanced with respect to video"
		::= { utg2000c01v1Entry 255 }

		-- 1.3.6.1.4.1.10106.3.101291.1.1.257
		utg2000c01v1Delay2G3p0r OBJECT-TYPE
			SYNTAX DelayX1Ms
			MAX-ACCESS read-only
			STATUS current
			DESCRIPTION
				"A negative value implies that audio is advanced with respect to video"
		::= { utg2000c01v1Entry 257 }

		-- 1.3.6.1.4.1.10106.3.101291.1.1.259
		utg2000c01v1Delay2G3p1l OBJECT-TYPE
			SYNTAX DelayX1Ms
			MAX-ACCESS read-only
			STATUS current
			DESCRIPTION
				"A negative value implies that audio is advanced with respect to video"
		::= { utg2000c01v1Entry 259 }

		-- 1.3.6.1.4.1.10106.3.101291.1.1.261
		utg2000c01v1Delay2G3p1r OBJECT-TYPE
			SYNTAX DelayX1Ms
			MAX-ACCESS read-only
			STATUS current
			DESCRIPTION
				"A negative value implies that audio is advanced with respect to video"
		::= { utg2000c01v1Entry 261 }

		-- 1.3.6.1.4.1.10106.3.101291.1.1.263
		utg2000c01v1Delay2G4p0l OBJECT-TYPE
			SYNTAX DelayX1Ms
			MAX-ACCESS read-only
			STATUS current
			DESCRIPTION
				"A negative value implies that audio is advanced with respect to video"
		::= { utg2000c01v1Entry 263 }

		-- 1.3.6.1.4.1.10106.3.101291.1.1.265
		utg2000c01v1Delay2G4p0r OBJECT-TYPE
			SYNTAX DelayX1Ms
			MAX-ACCESS read-only
			STATUS current
			DESCRIPTION
				"A negative value implies that audio is advanced with respect to video"
		::= { utg2000c01v1Entry 265 }

		-- 1.3.6.1.4.1.10106.3.101291.1.1.267
		utg2000c01v1Delay2G4p1l OBJECT-TYPE
			SYNTAX DelayX1Ms
			MAX-ACCESS read-only
			STATUS current
			DESCRIPTION
				"A negative value implies that audio is advanced with respect to video"
		::= { utg2000c01v1Entry 267 }

		-- 1.3.6.1.4.1.10106.3.101291.1.1.269
		utg2000c01v1Delay2G4p1r OBJECT-TYPE
			SYNTAX DelayX1Ms
			MAX-ACCESS read-only
			STATUS current
			DESCRIPTION
				"A negative value implies that audio is advanced with respect to video"
		::= { utg2000c01v1Entry 269 }

		-- 1.3.6.1.4.1.10106.3.101291.1.1.271
		utg2000c01v1Av2SeqG1p0 OBJECT-TYPE
			SYNTAX BitFail
			MAX-ACCESS read-only
			STATUS current
			DESCRIPTION
				"The A/V delay measurement sequence was not correctly detected for this pair"
		::= { utg2000c01v1Entry 271 }

		-- 1.3.6.1.4.1.10106.3.101291.1.1.273
		utg2000c01v1Av2SeqG1p1 OBJECT-TYPE
			SYNTAX BitFail
			MAX-ACCESS read-only
			STATUS current
			DESCRIPTION
				"The A/V delay measurement sequence was not correctly detected for this pair"
		::= { utg2000c01v1Entry 273 }

		-- 1.3.6.1.4.1.10106.3.101291.1.1.275
		utg2000c01v1Av2SeqG2p0 OBJECT-TYPE
			SYNTAX BitFail
			MAX-ACCESS read-only
			STATUS current
			DESCRIPTION
				"The A/V delay measurement sequence was not correctly detected for this pair"
		::= { utg2000c01v1Entry 275 }

		-- 1.3.6.1.4.1.10106.3.101291.1.1.277
		utg2000c01v1Av2SeqG2p1 OBJECT-TYPE
			SYNTAX BitFail
			MAX-ACCESS read-only
			STATUS current
			DESCRIPTION
				"The A/V delay measurement sequence was not correctly detected for this pair"
		::= { utg2000c01v1Entry 277 }

		-- 1.3.6.1.4.1.10106.3.101291.1.1.279
		utg2000c01v1Av2SeqG3p0 OBJECT-TYPE
			SYNTAX BitFail
			MAX-ACCESS read-only
			STATUS current
			DESCRIPTION
				"The A/V delay measurement sequence was not correctly detected for this pair"
		::= { utg2000c01v1Entry 279 }

		-- 1.3.6.1.4.1.10106.3.101291.1.1.281
		utg2000c01v1Av2SeqG3p1 OBJECT-TYPE
			SYNTAX BitFail
			MAX-ACCESS read-only
			STATUS current
			DESCRIPTION
				"The A/V delay measurement sequence was not correctly detected for this pair"
		::= { utg2000c01v1Entry 281 }

		-- 1.3.6.1.4.1.10106.3.101291.1.1.283
		utg2000c01v1Av2SeqG4p0 OBJECT-TYPE
			SYNTAX BitFail
			MAX-ACCESS read-only
			STATUS current
			DESCRIPTION
				"The A/V delay measurement sequence was not correctly detected for this pair"
		::= { utg2000c01v1Entry 283 }

		-- 1.3.6.1.4.1.10106.3.101291.1.1.285
		utg2000c01v1Av2SeqG4p1 OBJECT-TYPE
			SYNTAX BitFail
			MAX-ACCESS read-only
			STATUS current
			DESCRIPTION
				"The A/V delay measurement sequence was not correctly detected for this pair"
		::= { utg2000c01v1Entry 285 }

		-- 1.3.6.1.4.1.10106.3.101291.1.1.287
		utg2000c01v1Aud2GrpPres1 OBJECT-TYPE
			SYNTAX BitFailN
			MAX-ACCESS read-only
			STATUS current
			DESCRIPTION
				"Group 1 present"
		::= { utg2000c01v1Entry 287 }

		-- 1.3.6.1.4.1.10106.3.101291.1.1.289
		utg2000c01v1Aud2GrpPres2 OBJECT-TYPE
			SYNTAX BitFailN
			MAX-ACCESS read-only
			STATUS current
			DESCRIPTION
				"Group 2 present"
		::= { utg2000c01v1Entry 289 }

		-- 1.3.6.1.4.1.10106.3.101291.1.1.291
		utg2000c01v1Aud2GrpPres3 OBJECT-TYPE
			SYNTAX BitFailN
			MAX-ACCESS read-only
			STATUS current
			DESCRIPTION
				"Group 3 present"
		::= { utg2000c01v1Entry 291 }

		-- 1.3.6.1.4.1.10106.3.101291.1.1.293
		utg2000c01v1Aud2GrpPres4 OBJECT-TYPE
			SYNTAX BitFailN
			MAX-ACCESS read-only
			STATUS current
			DESCRIPTION
				"Group 4 present"
		::= { utg2000c01v1Entry 293 }

		-- 1.3.6.1.4.1.10106.3.101291.1.1.295
		utg2000c01v1Av2SeqPhase OBJECT-TYPE
			SYNTAX Uint8
			MAX-ACCESS read-only
			STATUS current
			DESCRIPTION
				"Seconds remaining until next delay measurement sequence starts"
		::= { utg2000c01v1Entry 295 }

		-- 1.3.6.1.4.1.10106.3.101291.1.1.297
		utg2000c01v1Delay3G1p0l OBJECT-TYPE
			SYNTAX DelayX1Ms
			MAX-ACCESS read-only
			STATUS current
			DESCRIPTION
				"A negative value implies that audio is advanced with respect to video"
		::= { utg2000c01v1Entry 297 }

		-- 1.3.6.1.4.1.10106.3.101291.1.1.299
		utg2000c01v1Delay3G1p0r OBJECT-TYPE
			SYNTAX DelayX1Ms
			MAX-ACCESS read-only
			STATUS current
			DESCRIPTION
				"A negative value implies that audio is advanced with respect to video"
		::= { utg2000c01v1Entry 299 }

		-- 1.3.6.1.4.1.10106.3.101291.1.1.301
		utg2000c01v1Delay3G1p1l OBJECT-TYPE
			SYNTAX DelayX1Ms
			MAX-ACCESS read-only
			STATUS current
			DESCRIPTION
				"A negative value implies that audio is advanced with respect to video"
		::= { utg2000c01v1Entry 301 }

		-- 1.3.6.1.4.1.10106.3.101291.1.1.303
		utg2000c01v1Delay3G1p1r OBJECT-TYPE
			SYNTAX DelayX1Ms
			MAX-ACCESS read-only
			STATUS current
			DESCRIPTION
				"A negative value implies that audio is advanced with respect to video"
		::= { utg2000c01v1Entry 303 }

		-- 1.3.6.1.4.1.10106.3.101291.1.1.305
		utg2000c01v1Delay3G2p0l OBJECT-TYPE
			SYNTAX DelayX1Ms
			MAX-ACCESS read-only
			STATUS current
			DESCRIPTION
				"A negative value implies that audio is advanced with respect to video"
		::= { utg2000c01v1Entry 305 }

		-- 1.3.6.1.4.1.10106.3.101291.1.1.307
		utg2000c01v1Delay3G2p0r OBJECT-TYPE
			SYNTAX DelayX1Ms
			MAX-ACCESS read-only
			STATUS current
			DESCRIPTION
				"A negative value implies that audio is advanced with respect to video"
		::= { utg2000c01v1Entry 307 }

		-- 1.3.6.1.4.1.10106.3.101291.1.1.309
		utg2000c01v1Delay3G2p1l OBJECT-TYPE
			SYNTAX DelayX1Ms
			MAX-ACCESS read-only
			STATUS current
			DESCRIPTION
				"A negative value implies that audio is advanced with respect to video"
		::= { utg2000c01v1Entry 309 }

		-- 1.3.6.1.4.1.10106.3.101291.1.1.311
		utg2000c01v1Delay3G2p1r OBJECT-TYPE
			SYNTAX DelayX1Ms
			MAX-ACCESS read-only
			STATUS current
			DESCRIPTION
				"A negative value implies that audio is advanced with respect to video"
		::= { utg2000c01v1Entry 311 }

		-- 1.3.6.1.4.1.10106.3.101291.1.1.313
		utg2000c01v1Delay3G3p0l OBJECT-TYPE
			SYNTAX DelayX1Ms
			MAX-ACCESS read-only
			STATUS current
			DESCRIPTION
				"A negative value implies that audio is advanced with respect to video"
		::= { utg2000c01v1Entry 313 }

		-- 1.3.6.1.4.1.10106.3.101291.1.1.315
		utg2000c01v1Delay3G3p0r OBJECT-TYPE
			SYNTAX DelayX1Ms
			MAX-ACCESS read-only
			STATUS current
			DESCRIPTION
				"A negative value implies that audio is advanced with respect to video"
		::= { utg2000c01v1Entry 315 }

		-- 1.3.6.1.4.1.10106.3.101291.1.1.317
		utg2000c01v1Delay3G3p1l OBJECT-TYPE
			SYNTAX DelayX1Ms
			MAX-ACCESS read-only
			STATUS current
			DESCRIPTION
				"A negative value implies that audio is advanced with respect to video"
		::= { utg2000c01v1Entry 317 }

		-- 1.3.6.1.4.1.10106.3.101291.1.1.319
		utg2000c01v1Delay3G3p1r OBJECT-TYPE
			SYNTAX DelayX1Ms
			MAX-ACCESS read-only
			STATUS current
			DESCRIPTION
				"A negative value implies that audio is advanced with respect to video"
		::= { utg2000c01v1Entry 319 }

		-- 1.3.6.1.4.1.10106.3.101291.1.1.321
		utg2000c01v1Delay3G4p0l OBJECT-TYPE
			SYNTAX DelayX1Ms
			MAX-ACCESS read-only
			STATUS current
			DESCRIPTION
				"A negative value implies that audio is advanced with respect to video"
		::= { utg2000c01v1Entry 321 }

		-- 1.3.6.1.4.1.10106.3.101291.1.1.323
		utg2000c01v1Delay3G4p0r OBJECT-TYPE
			SYNTAX DelayX1Ms
			MAX-ACCESS read-only
			STATUS current
			DESCRIPTION
				"A negative value implies that audio is advanced with respect to video"
		::= { utg2000c01v1Entry 323 }

		-- 1.3.6.1.4.1.10106.3.101291.1.1.325
		utg2000c01v1Delay3G4p1l OBJECT-TYPE
			SYNTAX DelayX1Ms
			MAX-ACCESS read-only
			STATUS current
			DESCRIPTION
				"A negative value implies that audio is advanced with respect to video"
		::= { utg2000c01v1Entry 325 }

		-- 1.3.6.1.4.1.10106.3.101291.1.1.327
		utg2000c01v1Delay3G4p1r OBJECT-TYPE
			SYNTAX DelayX1Ms
			MAX-ACCESS read-only
			STATUS current
			DESCRIPTION
				"A negative value implies that audio is advanced with respect to video"
		::= { utg2000c01v1Entry 327 }

		-- 1.3.6.1.4.1.10106.3.101291.1.1.329
		utg2000c01v1Av3SeqG1p0 OBJECT-TYPE
			SYNTAX BitFail
			MAX-ACCESS read-only
			STATUS current
			DESCRIPTION
				"The A/V delay measurement sequence was not correctly detected for this pair"
		::= { utg2000c01v1Entry 329 }

		-- 1.3.6.1.4.1.10106.3.101291.1.1.331
		utg2000c01v1Av3SeqG1p1 OBJECT-TYPE
			SYNTAX BitFail
			MAX-ACCESS read-only
			STATUS current
			DESCRIPTION
				"The A/V delay measurement sequence was not correctly detected for this pair"
		::= { utg2000c01v1Entry 331 }

		-- 1.3.6.1.4.1.10106.3.101291.1.1.333
		utg2000c01v1Av3SeqG2p0 OBJECT-TYPE
			SYNTAX BitFail
			MAX-ACCESS read-only
			STATUS current
			DESCRIPTION
				"The A/V delay measurement sequence was not correctly detected for this pair"
		::= { utg2000c01v1Entry 333 }

		-- 1.3.6.1.4.1.10106.3.101291.1.1.335
		utg2000c01v1Av3SeqG2p1 OBJECT-TYPE
			SYNTAX BitFail
			MAX-ACCESS read-only
			STATUS current
			DESCRIPTION
				"The A/V delay measurement sequence was not correctly detected for this pair"
		::= { utg2000c01v1Entry 335 }

		-- 1.3.6.1.4.1.10106.3.101291.1.1.337
		utg2000c01v1Av3SeqG3p0 OBJECT-TYPE
			SYNTAX BitFail
			MAX-ACCESS read-only
			STATUS current
			DESCRIPTION
				"The A/V delay measurement sequence was not correctly detected for this pair"
		::= { utg2000c01v1Entry 337 }

		-- 1.3.6.1.4.1.10106.3.101291.1.1.339
		utg2000c01v1Av3SeqG3p1 OBJECT-TYPE
			SYNTAX BitFail
			MAX-ACCESS read-only
			STATUS current
			DESCRIPTION
				"The A/V delay measurement sequence was not correctly detected for this pair"
		::= { utg2000c01v1Entry 339 }

		-- 1.3.6.1.4.1.10106.3.101291.1.1.341
		utg2000c01v1Av3SeqG4p0 OBJECT-TYPE
			SYNTAX BitFail
			MAX-ACCESS read-only
			STATUS current
			DESCRIPTION
				"The A/V delay measurement sequence was not correctly detected for this pair"
		::= { utg2000c01v1Entry 341 }

		-- 1.3.6.1.4.1.10106.3.101291.1.1.343
		utg2000c01v1Av3SeqG4p1 OBJECT-TYPE
			SYNTAX BitFail
			MAX-ACCESS read-only
			STATUS current
			DESCRIPTION
				"The A/V delay measurement sequence was not correctly detected for this pair"
		::= { utg2000c01v1Entry 343 }

		-- 1.3.6.1.4.1.10106.3.101291.1.1.345
		utg2000c01v1Aud3GrpPres1 OBJECT-TYPE
			SYNTAX BitFailN
			MAX-ACCESS read-only
			STATUS current
			DESCRIPTION
				"Group 1 present"
		::= { utg2000c01v1Entry 345 }

		-- 1.3.6.1.4.1.10106.3.101291.1.1.347
		utg2000c01v1Aud3GrpPres2 OBJECT-TYPE
			SYNTAX BitFailN
			MAX-ACCESS read-only
			STATUS current
			DESCRIPTION
				"Group 2 present"
		::= { utg2000c01v1Entry 347 }

		-- 1.3.6.1.4.1.10106.3.101291.1.1.349
		utg2000c01v1Aud3GrpPres3 OBJECT-TYPE
			SYNTAX BitFailN
			MAX-ACCESS read-only
			STATUS current
			DESCRIPTION
				"Group 3 present"
		::= { utg2000c01v1Entry 349 }

		-- 1.3.6.1.4.1.10106.3.101291.1.1.351
		utg2000c01v1Aud3GrpPres4 OBJECT-TYPE
			SYNTAX BitFailN
			MAX-ACCESS read-only
			STATUS current
			DESCRIPTION
				"Group 4 present"
		::= { utg2000c01v1Entry 351 }

		-- 1.3.6.1.4.1.10106.3.101291.1.1.353
		utg2000c01v1Av3SeqPhase OBJECT-TYPE
			SYNTAX Uint8
			MAX-ACCESS read-only
			STATUS current
			DESCRIPTION
				"Seconds remaining until next delay measurement sequence starts"
		::= { utg2000c01v1Entry 353 }

		-- 1.3.6.1.4.1.10106.3.101291.1.1.355
		utg2000c01v1DelayG1p0l OBJECT-TYPE
			SYNTAX DelayX1Ms
			MAX-ACCESS read-only
			STATUS current
			DESCRIPTION
				"A negative value implies that audio is advanced with respect to video"
		::= { utg2000c01v1Entry 355 }

		-- 1.3.6.1.4.1.10106.3.101291.1.1.357
		utg2000c01v1DelayG1p0r OBJECT-TYPE
			SYNTAX DelayX1Ms
			MAX-ACCESS read-only
			STATUS current
			DESCRIPTION
				"A negative value implies that audio is advanced with respect to video"
		::= { utg2000c01v1Entry 357 }

		-- 1.3.6.1.4.1.10106.3.101291.1.1.359
		utg2000c01v1DelayG1p1l OBJECT-TYPE
			SYNTAX DelayX1Ms
			MAX-ACCESS read-only
			STATUS current
			DESCRIPTION
				"A negative value implies that audio is advanced with respect to video"
		::= { utg2000c01v1Entry 359 }

		-- 1.3.6.1.4.1.10106.3.101291.1.1.361
		utg2000c01v1DelayG1p1r OBJECT-TYPE
			SYNTAX DelayX1Ms
			MAX-ACCESS read-only
			STATUS current
			DESCRIPTION
				"A negative value implies that audio is advanced with respect to video"
		::= { utg2000c01v1Entry 361 }

		-- 1.3.6.1.4.1.10106.3.101291.1.1.363
		utg2000c01v1DelayG2p0l OBJECT-TYPE
			SYNTAX DelayX1Ms
			MAX-ACCESS read-only
			STATUS current
			DESCRIPTION
				"A negative value implies that audio is advanced with respect to video"
		::= { utg2000c01v1Entry 363 }

		-- 1.3.6.1.4.1.10106.3.101291.1.1.365
		utg2000c01v1DelayG2p0r OBJECT-TYPE
			SYNTAX DelayX1Ms
			MAX-ACCESS read-only
			STATUS current
			DESCRIPTION
				"A negative value implies that audio is advanced with respect to video"
		::= { utg2000c01v1Entry 365 }

		-- 1.3.6.1.4.1.10106.3.101291.1.1.367
		utg2000c01v1DelayG2p1l OBJECT-TYPE
			SYNTAX DelayX1Ms
			MAX-ACCESS read-only
			STATUS current
			DESCRIPTION
				"A negative value implies that audio is advanced with respect to video"
		::= { utg2000c01v1Entry 367 }

		-- 1.3.6.1.4.1.10106.3.101291.1.1.369
		utg2000c01v1DelayG2p1r OBJECT-TYPE
			SYNTAX DelayX1Ms
			MAX-ACCESS read-only
			STATUS current
			DESCRIPTION
				"A negative value implies that audio is advanced with respect to video"
		::= { utg2000c01v1Entry 369 }

		-- 1.3.6.1.4.1.10106.3.101291.1.1.371
		utg2000c01v1DelayG3p0l OBJECT-TYPE
			SYNTAX DelayX1Ms
			MAX-ACCESS read-only
			STATUS current
			DESCRIPTION
				"A negative value implies that audio is advanced with respect to video"
		::= { utg2000c01v1Entry 371 }

		-- 1.3.6.1.4.1.10106.3.101291.1.1.373
		utg2000c01v1DelayG3p0r OBJECT-TYPE
			SYNTAX DelayX1Ms
			MAX-ACCESS read-only
			STATUS current
			DESCRIPTION
				"A negative value implies that audio is advanced with respect to video"
		::= { utg2000c01v1Entry 373 }

		-- 1.3.6.1.4.1.10106.3.101291.1.1.375
		utg2000c01v1DelayG3p1l OBJECT-TYPE
			SYNTAX DelayX1Ms
			MAX-ACCESS read-only
			STATUS current
			DESCRIPTION
				"A negative value implies that audio is advanced with respect to video"
		::= { utg2000c01v1Entry 375 }

		-- 1.3.6.1.4.1.10106.3.101291.1.1.377
		utg2000c01v1DelayG3p1r OBJECT-TYPE
			SYNTAX DelayX1Ms
			MAX-ACCESS read-only
			STATUS current
			DESCRIPTION
				"A negative value implies that audio is advanced with respect to video"
		::= { utg2000c01v1Entry 377 }

		-- 1.3.6.1.4.1.10106.3.101291.1.1.379
		utg2000c01v1DelayG4p0l OBJECT-TYPE
			SYNTAX DelayX1Ms
			MAX-ACCESS read-only
			STATUS current
			DESCRIPTION
				"A negative value implies that audio is advanced with respect to video"
		::= { utg2000c01v1Entry 379 }

		-- 1.3.6.1.4.1.10106.3.101291.1.1.381
		utg2000c01v1DelayG4p0r OBJECT-TYPE
			SYNTAX DelayX1Ms
			MAX-ACCESS read-only
			STATUS current
			DESCRIPTION
				"A negative value implies that audio is advanced with respect to video"
		::= { utg2000c01v1Entry 381 }

		-- 1.3.6.1.4.1.10106.3.101291.1.1.383
		utg2000c01v1DelayG4p1l OBJECT-TYPE
			SYNTAX DelayX1Ms
			MAX-ACCESS read-only
			STATUS current
			DESCRIPTION
				"A negative value implies that audio is advanced with respect to video"
		::= { utg2000c01v1Entry 383 }

		-- 1.3.6.1.4.1.10106.3.101291.1.1.385
		utg2000c01v1DelayG4p1r OBJECT-TYPE
			SYNTAX DelayX1Ms
			MAX-ACCESS read-only
			STATUS current
			DESCRIPTION
				"A negative value implies that audio is advanced with respect to video"
		::= { utg2000c01v1Entry 385 }

		-- 1.3.6.1.4.1.10106.3.101291.1.1.387
		utg2000c01v1AvSeqG1p0 OBJECT-TYPE
			SYNTAX BitFail
			MAX-ACCESS read-only
			STATUS current
			DESCRIPTION
				"The A/V delay measurement sequence was not correctly detected for this pair"
		::= { utg2000c01v1Entry 387 }

		-- 1.3.6.1.4.1.10106.3.101291.1.1.389
		utg2000c01v1AvSeqG1p1 OBJECT-TYPE
			SYNTAX BitFail
			MAX-ACCESS read-only
			STATUS current
			DESCRIPTION
				"The A/V delay measurement sequence was not correctly detected for this pair"
		::= { utg2000c01v1Entry 389 }

		-- 1.3.6.1.4.1.10106.3.101291.1.1.391
		utg2000c01v1AvSeqG2p0 OBJECT-TYPE
			SYNTAX BitFail
			MAX-ACCESS read-only
			STATUS current
			DESCRIPTION
				"The A/V delay measurement sequence was not correctly detected for this pair"
		::= { utg2000c01v1Entry 391 }

		-- 1.3.6.1.4.1.10106.3.101291.1.1.393
		utg2000c01v1AvSeqG2p1 OBJECT-TYPE
			SYNTAX BitFail
			MAX-ACCESS read-only
			STATUS current
			DESCRIPTION
				"The A/V delay measurement sequence was not correctly detected for this pair"
		::= { utg2000c01v1Entry 393 }

		-- 1.3.6.1.4.1.10106.3.101291.1.1.395
		utg2000c01v1AvSeqG3p0 OBJECT-TYPE
			SYNTAX BitFail
			MAX-ACCESS read-only
			STATUS current
			DESCRIPTION
				"The A/V delay measurement sequence was not correctly detected for this pair"
		::= { utg2000c01v1Entry 395 }

		-- 1.3.6.1.4.1.10106.3.101291.1.1.397
		utg2000c01v1AvSeqG3p1 OBJECT-TYPE
			SYNTAX BitFail
			MAX-ACCESS read-only
			STATUS current
			DESCRIPTION
				"The A/V delay measurement sequence was not correctly detected for this pair"
		::= { utg2000c01v1Entry 397 }

		-- 1.3.6.1.4.1.10106.3.101291.1.1.399
		utg2000c01v1AvSeqG4p0 OBJECT-TYPE
			SYNTAX BitFail
			MAX-ACCESS read-only
			STATUS current
			DESCRIPTION
				"The A/V delay measurement sequence was not correctly detected for this pair"
		::= { utg2000c01v1Entry 399 }

		-- 1.3.6.1.4.1.10106.3.101291.1.1.401
		utg2000c01v1AvSeqG4p1 OBJECT-TYPE
			SYNTAX BitFail
			MAX-ACCESS read-only
			STATUS current
			DESCRIPTION
				"The A/V delay measurement sequence was not correctly detected for this pair"
		::= { utg2000c01v1Entry 401 }

		-- 1.3.6.1.4.1.10106.3.101291.1.1.403
		utg2000c01v1AudGrpPres1 OBJECT-TYPE
			SYNTAX BitFailN
			MAX-ACCESS read-only
			STATUS current
			DESCRIPTION
				"Group 1 present"
		::= { utg2000c01v1Entry 403 }

		-- 1.3.6.1.4.1.10106.3.101291.1.1.405
		utg2000c01v1AudGrpPres2 OBJECT-TYPE
			SYNTAX BitFailN
			MAX-ACCESS read-only
			STATUS current
			DESCRIPTION
				"Group 2 present"
		::= { utg2000c01v1Entry 405 }

		-- 1.3.6.1.4.1.10106.3.101291.1.1.407
		utg2000c01v1AudGrpPres3 OBJECT-TYPE
			SYNTAX BitFailN
			MAX-ACCESS read-only
			STATUS current
			DESCRIPTION
				"Group 3 present"
		::= { utg2000c01v1Entry 407 }

		-- 1.3.6.1.4.1.10106.3.101291.1.1.409
		utg2000c01v1AudGrpPres4 OBJECT-TYPE
			SYNTAX BitFailN
			MAX-ACCESS read-only
			STATUS current
			DESCRIPTION
				"Group 4 present"
		::= { utg2000c01v1Entry 409 }

		-- 1.3.6.1.4.1.10106.3.101291.1.1.411
		utg2000c01v1AvSeqPhase OBJECT-TYPE
			SYNTAX Uint8
			MAX-ACCESS read-only
			STATUS current
			DESCRIPTION
				"Seconds remaining until next delay measurement sequence starts"
		::= { utg2000c01v1Entry 411 }

		-- 1.3.6.1.4.1.10106.3.101291.1.1.413
		utg2000c01v1ArefFail OBJECT-TYPE
			SYNTAX BitFail
			MAX-ACCESS read-only
			STATUS current
			DESCRIPTION
				"Indicates the absence of analog reference"
		::= { utg2000c01v1Entry 413 }

		-- 1.3.6.1.4.1.10106.3.101291.1.1.414
		utg2000c01v1ArefFailTrapEnable OBJECT-TYPE
			SYNTAX AlarmEnable
			MAX-ACCESS read-write
			STATUS current
			DESCRIPTION
				"Indicates the absence of analog reference Trap Enable"
		::= { utg2000c01v1Entry 414 }

		-- 1.3.6.1.4.1.10106.3.101291.1.1.415
		utg2000c01v1DrefFail OBJECT-TYPE
			SYNTAX BitFail
			MAX-ACCESS read-only
			STATUS current
			DESCRIPTION
				"Indicates the absence of digital reference"
		::= { utg2000c01v1Entry 415 }

		-- 1.3.6.1.4.1.10106.3.101291.1.1.416
		utg2000c01v1DrefFailTrapEnable OBJECT-TYPE
			SYNTAX AlarmEnable
			MAX-ACCESS read-write
			STATUS current
			DESCRIPTION
				"Indicates the absence of digital reference Trap Enable"
		::= { utg2000c01v1Entry 416 }

		-- 1.3.6.1.4.1.10106.3.101291.1.1.417
		utg2000c01v1IrefFail OBJECT-TYPE
			SYNTAX BitFail
			MAX-ACCESS read-only
			STATUS current
			DESCRIPTION
				"Indicates the absence of internal reference"
		::= { utg2000c01v1Entry 417 }

		-- 1.3.6.1.4.1.10106.3.101291.1.1.418
		utg2000c01v1IrefFailTrapEnable OBJECT-TYPE
			SYNTAX AlarmEnable
			MAX-ACCESS read-write
			STATUS current
			DESCRIPTION
				"Indicates the absence of internal reference Trap Enable"
		::= { utg2000c01v1Entry 418 }

		-- 1.3.6.1.4.1.10106.3.101291.1.1.419
		utg2000c01v1RefIncFail OBJECT-TYPE
			SYNTAX BitFail
			MAX-ACCESS read-only
			STATUS current
			DESCRIPTION
				"Indicates that the format of the received reference is different from expected"
		::= { utg2000c01v1Entry 419 }

		-- 1.3.6.1.4.1.10106.3.101291.1.1.420
		utg2000c01v1RefIncFailTrapEnable OBJECT-TYPE
			SYNTAX AlarmEnable
			MAX-ACCESS read-write
			STATUS current
			DESCRIPTION
				"Indicates that the format of the received reference is different from expected Trap Enable"
		::= { utg2000c01v1Entry 420 }

		-- 1.3.6.1.4.1.10106.3.101291.1.1.421
		utg2000c01v1RefLockFail OBJECT-TYPE
			SYNTAX BitFail
			MAX-ACCESS read-only
			STATUS current
			DESCRIPTION
				"Indicates that the module is not locked to the reference"
		::= { utg2000c01v1Entry 421 }

		-- 1.3.6.1.4.1.10106.3.101291.1.1.422
		utg2000c01v1RefLockFailTrapEnable OBJECT-TYPE
			SYNTAX AlarmEnable
			MAX-ACCESS read-write
			STATUS current
			DESCRIPTION
				"Indicates that the module is not locked to the reference Trap Enable"
		::= { utg2000c01v1Entry 422 }

		-- 1.3.6.1.4.1.10106.3.101291.1.1.423
		utg2000c01v1DrefCrcFail OBJECT-TYPE
			SYNTAX BitFail
			MAX-ACCESS read-only
			STATUS current
			DESCRIPTION
				"Indicates that the digital reference has CRC/EDH errors"
		::= { utg2000c01v1Entry 423 }

		-- 1.3.6.1.4.1.10106.3.101291.1.1.424
		utg2000c01v1DrefCrcFailTrapEnable OBJECT-TYPE
			SYNTAX AlarmEnable
			MAX-ACCESS read-write
			STATUS current
			DESCRIPTION
				"Indicates that the digital reference has CRC/EDH errors Trap Enable"
		::= { utg2000c01v1Entry 424 }

		-- 1.3.6.1.4.1.10106.3.101291.1.1.425
		utg2000c01v1TcFail OBJECT-TYPE
			SYNTAX BitFail
			MAX-ACCESS read-only
			STATUS current
			DESCRIPTION
				"Indicates the absence of time and date information in the internal reference"
		::= { utg2000c01v1Entry 425 }

		-- 1.3.6.1.4.1.10106.3.101291.1.1.427
		utg2000c01v1LogoRdy1 OBJECT-TYPE
			SYNTAX Bit0No1Yes
			MAX-ACCESS read-only
			STATUS current
			DESCRIPTION
				"Indicates that the layer is currently being rendered and cannot be shown"
		::= { utg2000c01v1Entry 427 }

		-- 1.3.6.1.4.1.10106.3.101291.1.1.429
		utg2000c01v1ArefFormat OBJECT-TYPE
			SYNTAX SdiHd12gFmt2
			MAX-ACCESS read-only
			STATUS current
			DESCRIPTION
				"Indicates the detected format of the analog reference"
		::= { utg2000c01v1Entry 429 }

		-- 1.3.6.1.4.1.10106.3.101291.1.1.430
		utg2000c01v1ArefFormatTrapEnable OBJECT-TYPE
			SYNTAX AlarmEnable
			MAX-ACCESS read-write
			STATUS current
			DESCRIPTION
				"Indicates the detected format of the analog reference Trap Enable"
		::= { utg2000c01v1Entry 430 }

		-- 1.3.6.1.4.1.10106.3.101291.1.1.431
		utg2000c01v1DrefFormat OBJECT-TYPE
			SYNTAX SdiHd12gFmt2
			MAX-ACCESS read-only
			STATUS current
			DESCRIPTION
				"Indicates the detected format of the digital reference"
		::= { utg2000c01v1Entry 431 }

		-- 1.3.6.1.4.1.10106.3.101291.1.1.432
		utg2000c01v1DrefFormatTrapEnable OBJECT-TYPE
			SYNTAX AlarmEnable
			MAX-ACCESS read-write
			STATUS current
			DESCRIPTION
				"Indicates the detected format of the digital reference Trap Enable"
		::= { utg2000c01v1Entry 432 }

		-- 1.3.6.1.4.1.10106.3.101291.1.1.433
		utg2000c01v1CrcErrors OBJECT-TYPE
			SYNTAX Uint8
			MAX-ACCESS read-only
			STATUS current
			DESCRIPTION
				"Indicates the CRC/EDH errors"
		::= { utg2000c01v1Entry 433 }

		-- 1.3.6.1.4.1.10106.3.101291.1.1.435
		utg2000c01v1InputFailures OBJECT-TYPE
			SYNTAX Uint8
			MAX-ACCESS read-only
			STATUS current
			DESCRIPTION
				"The number of SDI input failure"
		::= { utg2000c01v1Entry 435 }

		-- 1.3.6.1.4.1.10106.3.101291.1.1.437
		utg2000c01v1MeasDelay OBJECT-TYPE
			SYNTAX DelayX74Ns
			MAX-ACCESS read-only
			STATUS current
			DESCRIPTION
				"Indicates the delay measured between references"
		::= { utg2000c01v1Entry 437 }

		-- 1.3.6.1.4.1.10106.3.101291.1.1.439
		utg2000c01v1MeasFreq OBJECT-TYPE
			SYNTAX FrqDrft3
			MAX-ACCESS read-only
			STATUS current
			DESCRIPTION
				"Indicates the measured frequency deviation"
		::= { utg2000c01v1Entry 439 }

		-- 1.3.6.1.4.1.10106.3.101291.1.1.441
		utg2000c01v1SfpType OBJECT-TYPE
			SYNTAX SfpType2
			MAX-ACCESS read-only
			STATUS current
			DESCRIPTION
				"SFP type"
		::= { utg2000c01v1Entry 441 }

		-- 1.3.6.1.4.1.10106.3.101291.1.1.443
		utg2000c01v1SfpTemp OBJECT-TYPE
			SYNTAX Temperature0c1
			MAX-ACCESS read-only
			STATUS current
			DESCRIPTION
				"SFP Temperature"
		::= { utg2000c01v1Entry 443 }

		-- 1.3.6.1.4.1.10106.3.101291.1.1.445
		utg2000c01v1SfpRxPower OBJECT-TYPE
			SYNTAX OptPowerX2Uw
			MAX-ACCESS read-only
			STATUS current
			DESCRIPTION
				"Optical received power"
		::= { utg2000c01v1Entry 445 }

		-- 1.3.6.1.4.1.10106.3.101291.1.1.447
		utg2000c01v1SerialNo OBJECT-TYPE
			SYNTAX SerialNo
			MAX-ACCESS read-only
			STATUS current
			DESCRIPTION
				"Serial number"
		::= { utg2000c01v1Entry 447 }

		-- 1.3.6.1.4.1.10106.3.579101
		hvd2002c01v1 OBJECT IDENTIFIER ::= { albalaProducts 579101 }

		-- 1.3.6.1.4.1.10106.3.579101.1
		hvd2002c01v1Table  OBJECT-TYPE
			SYNTAX SEQUENCE OF Hvd2002c01v1Entry
			MAX-ACCESS not-accessible
			STATUS current
			DESCRIPTION
				"Module  HVD2002C01V1 Table"
			::= { hvd2002c01v1 1 }

		-- 1.3.6.1.4.1.10106.3.579101.1.1
		hvd2002c01v1Entry  OBJECT-TYPE
			SYNTAX Hvd2002c01v1Entry
			MAX-ACCESS not-accessible
			STATUS current
			DESCRIPTION
				"Module HVD2002C01V1 Entry"
			INDEX { hvd2002c01v1Index }
			::= { hvd2002c01v1Table 1 }

			Hvd2002c01v1Entry ::=
			SEQUENCE {
				hvd2002c01v1Index
				ModuleIndex,
				hvd2002c01v1InputSel
				Hvp2Input,
				hvd2002c01v1Bck0Sel
				Hvp2Input,
				hvd2002c01v1Bck1Sel
				Hvp2Input,
				hvd2002c01v1NoSig
				BitFail,
				hvd2002c01v1NoSigTrapEnable
				AlarmEnable,
				hvd2002c01v1Unlock
				BitFail,
				hvd2002c01v1UnlockTrapEnable
				AlarmEnable,
				hvd2002c01v1Hd
				Bit0Sd1Hd,
				hvd2002c01v1SerialNo
				SerialNo
			 }

		-- 1.3.6.1.4.1.10106.3.101291.1.1.1
		hvd2002c01v1Index OBJECT-TYPE
			SYNTAX ModuleIndex
			MAX-ACCESS read-only
			STATUS current
			DESCRIPTION
				"Index of HVD2002C01V1 Table"
		::= { hvd2002c01v1Entry 1 }

		-- 1.3.6.1.4.1.10106.3.101291.1.1.3
		hvd2002c01v1InputSel OBJECT-TYPE
			SYNTAX Hvp2Input
			MAX-ACCESS read-write
			STATUS current
			DESCRIPTION
				"Indicates the input selected"
		::= { hvd2002c01v1Entry 3 }

		-- 1.3.6.1.4.1.10106.3.101291.1.1.5
		hvd2002c01v1Bck0Sel OBJECT-TYPE
			SYNTAX Hvp2Input
			MAX-ACCESS read-write
			STATUS current
			DESCRIPTION
				"Enables the driver that transmit to backplane 0"
		::= { hvd2002c01v1Entry 5 }

		-- 1.3.6.1.4.1.10106.3.101291.1.1.7
		hvd2002c01v1Bck1Sel OBJECT-TYPE
			SYNTAX Hvp2Input
			MAX-ACCESS read-write
			STATUS current
			DESCRIPTION
				"Enables the driver that transmit to backplane 1"
		::= { hvd2002c01v1Entry 7 }

		-- 1.3.6.1.4.1.10106.3.101291.1.1.9
		hvd2002c01v1NoSig OBJECT-TYPE
			SYNTAX BitFail
			MAX-ACCESS read-only
			STATUS current
			DESCRIPTION
				"Input signal status"
		::= { hvd2002c01v1Entry 9 }

		-- 1.3.6.1.4.1.10106.3.101291.1.1.10
		hvd2002c01v1NoSigTrapEnable OBJECT-TYPE
			SYNTAX AlarmEnable
			MAX-ACCESS read-write
			STATUS current
			DESCRIPTION
				"Input signal status Trap Enable"
		::= { hvd2002c01v1Entry 10 }

		-- 1.3.6.1.4.1.10106.3.101291.1.1.11
		hvd2002c01v1Unlock OBJECT-TYPE
			SYNTAX BitFail
			MAX-ACCESS read-only
			STATUS current
			DESCRIPTION
				"Indicates signal unlock fail"
		::= { hvd2002c01v1Entry 11 }

		-- 1.3.6.1.4.1.10106.3.101291.1.1.12
		hvd2002c01v1UnlockTrapEnable OBJECT-TYPE
			SYNTAX AlarmEnable
			MAX-ACCESS read-write
			STATUS current
			DESCRIPTION
				"Indicates signal unlock fail Trap Enable"
		::= { hvd2002c01v1Entry 12 }

		-- 1.3.6.1.4.1.10106.3.101291.1.1.13
		hvd2002c01v1Hd OBJECT-TYPE
			SYNTAX Bit0Sd1Hd
			MAX-ACCESS read-only
			STATUS current
			DESCRIPTION
				"Indicates the SDI signal type"
		::= { hvd2002c01v1Entry 13 }

		-- 1.3.6.1.4.1.10106.3.101291.1.1.15
		hvd2002c01v1SerialNo OBJECT-TYPE
			SYNTAX SerialNo
			MAX-ACCESS read-only
			STATUS current
			DESCRIPTION
				"Serial number"
		::= { hvd2002c01v1Entry 15 }

		-- 1.3.6.1.4.1.10106.3.583701
		hfs2001c01v1 OBJECT IDENTIFIER ::= { albalaProducts 583701 }

		-- 1.3.6.1.4.1.10106.3.583701.1
		hfs2001c01v1Table  OBJECT-TYPE
			SYNTAX SEQUENCE OF Hfs2001c01v1Entry
			MAX-ACCESS not-accessible
			STATUS current
			DESCRIPTION
				"Module  HFS2001C01V1 Table"
			::= { hfs2001c01v1 1 }

		-- 1.3.6.1.4.1.10106.3.583701.1.1
		hfs2001c01v1Entry  OBJECT-TYPE
			SYNTAX Hfs2001c01v1Entry
			MAX-ACCESS not-accessible
			STATUS current
			DESCRIPTION
				"Module HFS2001C01V1 Entry"
			INDEX { hfs2001c01v1Index }
			::= { hfs2001c01v1Table 1 }

			Hfs2001c01v1Entry ::=
			SEQUENCE {
				hfs2001c01v1Index
				ModuleIndex,
				hfs2001c01v1SynchroMode
				Bit0Fra1Lin,
				hfs2001c01v1FailMode
				Bit0Fre1Blk,
				hfs2001c01v1VbiMode
				Bit0Pas1Bnk,
				hfs2001c01v1DelayMode
				Bit0Syn1De2,
				hfs2001c01v1HDelay
				DelayPixel5,
				hfs2001c01v1VDelay
				DelayLines2,
				hfs2001c01v1Bits
				Bit020124,
				hfs2001c01v1FrameDelay
				DelayFram2,
				hfs2001c01v1NoSig
				BitFail,
				hfs2001c01v1NoSigTrapEnable
				AlarmEnable,
				hfs2001c01v1Unlock
				BitFail,
				hfs2001c01v1UnlockTrapEnable
				AlarmEnable,
				hfs2001c01v1EdhCrc
				BitFail,
				hfs2001c01v1EdhCrcTrapEnable
				AlarmEnable,
				hfs2001c01v1NoRef
				BitFail,
				hfs2001c01v1NoRefTrapEnable
				AlarmEnable,
				hfs2001c01v1RefUnlock
				BitFail,
				hfs2001c01v1RefUnlockTrapEnable
				AlarmEnable,
				hfs2001c01v1InputFormat
				SdiHd3gFmt3,
				hfs2001c01v1SdiFormat
				SdiHd3gFmt3,
				hfs2001c01v1Grp1Pres
				Bit0No1Yes,
				hfs2001c01v1Grp2Pres
				Bit0No1Yes,
				hfs2001c01v1Grp3Pres
				Bit0No1Yes,
				hfs2001c01v1Grp4Pres
				Bit0No1Yes,
				hfs2001c01v1Grp1P0Err
				BitFail,
				hfs2001c01v1Grp1P1Err
				BitFail,
				hfs2001c01v1Grp2P0Err
				BitFail,
				hfs2001c01v1Grp2P1Err
				BitFail,
				hfs2001c01v1Grp3P0Err
				BitFail,
				hfs2001c01v1Grp3P1Err
				BitFail,
				hfs2001c01v1Grp4P0Err
				BitFail,
				hfs2001c01v1Grp4P1Err
				BitFail,
				hfs2001c01v1R2lIn1Pres
				BitFail,
				hfs2001c01v1R2lIn2Pres
				BitFail,
				hfs2001c01v1R2lIn3Pres
				BitFail,
				hfs2001c01v1R2lIn4Pres
				BitFail,
				hfs2001c01v1R2lIn5Pres
				BitFail,
				hfs2001c01v1R2lIn6Pres
				BitFail,
				hfs2001c01v1R2lIn7Pres
				BitFail,
				hfs2001c01v1R2lIn8Pres
				BitFail,
				hfs2001c01v1R2lIn9Pres
				BitFail,
				hfs2001c01v1R2lIn10Pres
				BitFail,
				hfs2001c01v1R2lIn11Pres
				BitFail,
				hfs2001c01v1R2lIn12Pres
				BitFail,
				hfs2001c01v1R2lIn13Pres
				BitFail,
				hfs2001c01v1R2lIn14Pres
				BitFail,
				hfs2001c01v1R2lIn15Pres
				BitFail,
				hfs2001c01v1R2lIn16Pres
				BitFail,
				hfs2001c01v1SerialNo
				SerialNo
			 }

		-- 1.3.6.1.4.1.10106.3.101291.1.1.1
		hfs2001c01v1Index OBJECT-TYPE
			SYNTAX ModuleIndex
			MAX-ACCESS read-only
			STATUS current
			DESCRIPTION
				"Index of HFS2001C01V1 Table"
		::= { hfs2001c01v1Entry 1 }

		-- 1.3.6.1.4.1.10106.3.101291.1.1.3
		hfs2001c01v1SynchroMode OBJECT-TYPE
			SYNTAX Bit0Fra1Lin
			MAX-ACCESS read-write
			STATUS current
			DESCRIPTION
				"Allows selecting the synchronizing mode"
		::= { hfs2001c01v1Entry 3 }

		-- 1.3.6.1.4.1.10106.3.101291.1.1.5
		hfs2001c01v1FailMode OBJECT-TYPE
			SYNTAX Bit0Fre1Blk
			MAX-ACCESS read-write
			STATUS current
			DESCRIPTION
				"Allows selecting the output video signal if the input fails"
		::= { hfs2001c01v1Entry 5 }

		-- 1.3.6.1.4.1.10106.3.101291.1.1.7
		hfs2001c01v1VbiMode OBJECT-TYPE
			SYNTAX Bit0Pas1Bnk
			MAX-ACCESS read-write
			STATUS current
			DESCRIPTION
				"Allows selecting if the VBI is blanked"
		::= { hfs2001c01v1Entry 7 }

		-- 1.3.6.1.4.1.10106.3.101291.1.1.9
		hfs2001c01v1DelayMode OBJECT-TYPE
			SYNTAX Bit0Syn1De2
			MAX-ACCESS read-write
			STATUS current
			DESCRIPTION
				"Allows selecting the operating mode"
		::= { hfs2001c01v1Entry 9 }

		-- 1.3.6.1.4.1.10106.3.101291.1.1.11
		hfs2001c01v1HDelay OBJECT-TYPE
			SYNTAX DelayPixel5
			MAX-ACCESS read-write
			STATUS current
			DESCRIPTION
				"Allows adjusting the video horizontal delay"
		::= { hfs2001c01v1Entry 11 }

		-- 1.3.6.1.4.1.10106.3.101291.1.1.13
		hfs2001c01v1VDelay OBJECT-TYPE
			SYNTAX DelayLines2
			MAX-ACCESS read-write
			STATUS current
			DESCRIPTION
				"Allows adjusting the video vertical delay"
		::= { hfs2001c01v1Entry 13 }

		-- 1.3.6.1.4.1.10106.3.101291.1.1.15
		hfs2001c01v1Bits OBJECT-TYPE
			SYNTAX Bit020124
			MAX-ACCESS read-write
			STATUS current
			DESCRIPTION
				"Audio sample precision in SD"
		::= { hfs2001c01v1Entry 15 }

		-- 1.3.6.1.4.1.10106.3.101291.1.1.17
		hfs2001c01v1FrameDelay OBJECT-TYPE
			SYNTAX DelayFram2
			MAX-ACCESS read-write
			STATUS current
			DESCRIPTION
				"Allows adjusting the frame delay"
		::= { hfs2001c01v1Entry 17 }

		-- 1.3.6.1.4.1.10106.3.101291.1.1.19
		hfs2001c01v1NoSig OBJECT-TYPE
			SYNTAX BitFail
			MAX-ACCESS read-only
			STATUS current
			DESCRIPTION
				"Indicates SDI signal fail"
		::= { hfs2001c01v1Entry 19 }

		-- 1.3.6.1.4.1.10106.3.101291.1.1.20
		hfs2001c01v1NoSigTrapEnable OBJECT-TYPE
			SYNTAX AlarmEnable
			MAX-ACCESS read-write
			STATUS current
			DESCRIPTION
				"Indicates SDI signal fail Trap Enable"
		::= { hfs2001c01v1Entry 20 }

		-- 1.3.6.1.4.1.10106.3.101291.1.1.21
		hfs2001c01v1Unlock OBJECT-TYPE
			SYNTAX BitFail
			MAX-ACCESS read-only
			STATUS current
			DESCRIPTION
				"Indicates signal unlock"
		::= { hfs2001c01v1Entry 21 }

		-- 1.3.6.1.4.1.10106.3.101291.1.1.22
		hfs2001c01v1UnlockTrapEnable OBJECT-TYPE
			SYNTAX AlarmEnable
			MAX-ACCESS read-write
			STATUS current
			DESCRIPTION
				"Indicates signal unlock Trap Enable"
		::= { hfs2001c01v1Entry 22 }

		-- 1.3.6.1.4.1.10106.3.101291.1.1.23
		hfs2001c01v1EdhCrc OBJECT-TYPE
			SYNTAX BitFail
			MAX-ACCESS read-only
			STATUS current
			DESCRIPTION
				"Indicates presence of EDH/CRC errors"
		::= { hfs2001c01v1Entry 23 }

		-- 1.3.6.1.4.1.10106.3.101291.1.1.24
		hfs2001c01v1EdhCrcTrapEnable OBJECT-TYPE
			SYNTAX AlarmEnable
			MAX-ACCESS read-write
			STATUS current
			DESCRIPTION
				"Indicates presence of EDH/CRC errors Trap Enable"
		::= { hfs2001c01v1Entry 24 }

		-- 1.3.6.1.4.1.10106.3.101291.1.1.25
		hfs2001c01v1NoRef OBJECT-TYPE
			SYNTAX BitFail
			MAX-ACCESS read-only
			STATUS current
			DESCRIPTION
				"Indicates reference signal fail"
		::= { hfs2001c01v1Entry 25 }

		-- 1.3.6.1.4.1.10106.3.101291.1.1.26
		hfs2001c01v1NoRefTrapEnable OBJECT-TYPE
			SYNTAX AlarmEnable
			MAX-ACCESS read-write
			STATUS current
			DESCRIPTION
				"Indicates reference signal fail Trap Enable"
		::= { hfs2001c01v1Entry 26 }

		-- 1.3.6.1.4.1.10106.3.101291.1.1.27
		hfs2001c01v1RefUnlock OBJECT-TYPE
			SYNTAX BitFail
			MAX-ACCESS read-only
			STATUS current
			DESCRIPTION
				"Indicates reference signal unlock fail"
		::= { hfs2001c01v1Entry 27 }

		-- 1.3.6.1.4.1.10106.3.101291.1.1.28
		hfs2001c01v1RefUnlockTrapEnable OBJECT-TYPE
			SYNTAX AlarmEnable
			MAX-ACCESS read-write
			STATUS current
			DESCRIPTION
				"Indicates reference signal unlock fail Trap Enable"
		::= { hfs2001c01v1Entry 28 }

		-- 1.3.6.1.4.1.10106.3.101291.1.1.29
		hfs2001c01v1InputFormat OBJECT-TYPE
			SYNTAX SdiHd3gFmt3
			MAX-ACCESS read-only
			STATUS current
			DESCRIPTION
				"Indicates the reference signal format"
		::= { hfs2001c01v1Entry 29 }

		-- 1.3.6.1.4.1.10106.3.101291.1.1.31
		hfs2001c01v1SdiFormat OBJECT-TYPE
			SYNTAX SdiHd3gFmt3
			MAX-ACCESS read-only
			STATUS current
			DESCRIPTION
				"Indicates the SDI input format"
		::= { hfs2001c01v1Entry 31 }

		-- 1.3.6.1.4.1.10106.3.101291.1.1.33
		hfs2001c01v1Grp1Pres OBJECT-TYPE
			SYNTAX Bit0No1Yes
			MAX-ACCESS read-only
			STATUS current
			DESCRIPTION
				"Group presence in SDI input"
		::= { hfs2001c01v1Entry 33 }

		-- 1.3.6.1.4.1.10106.3.101291.1.1.35
		hfs2001c01v1Grp2Pres OBJECT-TYPE
			SYNTAX Bit0No1Yes
			MAX-ACCESS read-only
			STATUS current
			DESCRIPTION
				"Group presence in SDI input"
		::= { hfs2001c01v1Entry 35 }

		-- 1.3.6.1.4.1.10106.3.101291.1.1.37
		hfs2001c01v1Grp3Pres OBJECT-TYPE
			SYNTAX Bit0No1Yes
			MAX-ACCESS read-only
			STATUS current
			DESCRIPTION
				"Group presence in SDI input"
		::= { hfs2001c01v1Entry 37 }

		-- 1.3.6.1.4.1.10106.3.101291.1.1.39
		hfs2001c01v1Grp4Pres OBJECT-TYPE
			SYNTAX Bit0No1Yes
			MAX-ACCESS read-only
			STATUS current
			DESCRIPTION
				"Group presence in SDI input"
		::= { hfs2001c01v1Entry 39 }

		-- 1.3.6.1.4.1.10106.3.101291.1.1.41
		hfs2001c01v1Grp1P0Err OBJECT-TYPE
			SYNTAX BitFail
			MAX-ACCESS read-only
			STATUS current
			DESCRIPTION
				"SDI group 1 pair 0 fail"
		::= { hfs2001c01v1Entry 41 }

		-- 1.3.6.1.4.1.10106.3.101291.1.1.43
		hfs2001c01v1Grp1P1Err OBJECT-TYPE
			SYNTAX BitFail
			MAX-ACCESS read-only
			STATUS current
			DESCRIPTION
				"SDI group 1 pair 1 fail"
		::= { hfs2001c01v1Entry 43 }

		-- 1.3.6.1.4.1.10106.3.101291.1.1.45
		hfs2001c01v1Grp2P0Err OBJECT-TYPE
			SYNTAX BitFail
			MAX-ACCESS read-only
			STATUS current
			DESCRIPTION
				"SDI group 2 pair 0 fail"
		::= { hfs2001c01v1Entry 45 }

		-- 1.3.6.1.4.1.10106.3.101291.1.1.47
		hfs2001c01v1Grp2P1Err OBJECT-TYPE
			SYNTAX BitFail
			MAX-ACCESS read-only
			STATUS current
			DESCRIPTION
				"SDI group 2 pair 1 fail"
		::= { hfs2001c01v1Entry 47 }

		-- 1.3.6.1.4.1.10106.3.101291.1.1.49
		hfs2001c01v1Grp3P0Err OBJECT-TYPE
			SYNTAX BitFail
			MAX-ACCESS read-only
			STATUS current
			DESCRIPTION
				"SDI group 3 pair 0 fail"
		::= { hfs2001c01v1Entry 49 }

		-- 1.3.6.1.4.1.10106.3.101291.1.1.51
		hfs2001c01v1Grp3P1Err OBJECT-TYPE
			SYNTAX BitFail
			MAX-ACCESS read-only
			STATUS current
			DESCRIPTION
				"SDI group 3 pair 1 fail"
		::= { hfs2001c01v1Entry 51 }

		-- 1.3.6.1.4.1.10106.3.101291.1.1.53
		hfs2001c01v1Grp4P0Err OBJECT-TYPE
			SYNTAX BitFail
			MAX-ACCESS read-only
			STATUS current
			DESCRIPTION
				"SDI group 4 pair 0 fail"
		::= { hfs2001c01v1Entry 53 }

		-- 1.3.6.1.4.1.10106.3.101291.1.1.55
		hfs2001c01v1Grp4P1Err OBJECT-TYPE
			SYNTAX BitFail
			MAX-ACCESS read-only
			STATUS current
			DESCRIPTION
				"SDI group 4 pair 1 fail"
		::= { hfs2001c01v1Entry 55 }

		-- 1.3.6.1.4.1.10106.3.101291.1.1.57
		hfs2001c01v1R2lIn1Pres OBJECT-TYPE
			SYNTAX BitFail
			MAX-ACCESS read-only
			STATUS current
			DESCRIPTION
				"R2L IN channel 1 fail"
		::= { hfs2001c01v1Entry 57 }

		-- 1.3.6.1.4.1.10106.3.101291.1.1.59
		hfs2001c01v1R2lIn2Pres OBJECT-TYPE
			SYNTAX BitFail
			MAX-ACCESS read-only
			STATUS current
			DESCRIPTION
				"R2L IN channel 2 fail"
		::= { hfs2001c01v1Entry 59 }

		-- 1.3.6.1.4.1.10106.3.101291.1.1.61
		hfs2001c01v1R2lIn3Pres OBJECT-TYPE
			SYNTAX BitFail
			MAX-ACCESS read-only
			STATUS current
			DESCRIPTION
				"R2L IN channel 3 fail"
		::= { hfs2001c01v1Entry 61 }

		-- 1.3.6.1.4.1.10106.3.101291.1.1.63
		hfs2001c01v1R2lIn4Pres OBJECT-TYPE
			SYNTAX BitFail
			MAX-ACCESS read-only
			STATUS current
			DESCRIPTION
				"R2L IN channel 4 fail"
		::= { hfs2001c01v1Entry 63 }

		-- 1.3.6.1.4.1.10106.3.101291.1.1.65
		hfs2001c01v1R2lIn5Pres OBJECT-TYPE
			SYNTAX BitFail
			MAX-ACCESS read-only
			STATUS current
			DESCRIPTION
				"R2L IN channel 5 fail"
		::= { hfs2001c01v1Entry 65 }

		-- 1.3.6.1.4.1.10106.3.101291.1.1.67
		hfs2001c01v1R2lIn6Pres OBJECT-TYPE
			SYNTAX BitFail
			MAX-ACCESS read-only
			STATUS current
			DESCRIPTION
				"R2L IN channel 6 fail"
		::= { hfs2001c01v1Entry 67 }

		-- 1.3.6.1.4.1.10106.3.101291.1.1.69
		hfs2001c01v1R2lIn7Pres OBJECT-TYPE
			SYNTAX BitFail
			MAX-ACCESS read-only
			STATUS current
			DESCRIPTION
				"R2L IN channel 7 fail"
		::= { hfs2001c01v1Entry 69 }

		-- 1.3.6.1.4.1.10106.3.101291.1.1.71
		hfs2001c01v1R2lIn8Pres OBJECT-TYPE
			SYNTAX BitFail
			MAX-ACCESS read-only
			STATUS current
			DESCRIPTION
				"R2L IN channel 8 fail"
		::= { hfs2001c01v1Entry 71 }

		-- 1.3.6.1.4.1.10106.3.101291.1.1.73
		hfs2001c01v1R2lIn9Pres OBJECT-TYPE
			SYNTAX BitFail
			MAX-ACCESS read-only
			STATUS current
			DESCRIPTION
				"R2L IN channel 9 fail"
		::= { hfs2001c01v1Entry 73 }

		-- 1.3.6.1.4.1.10106.3.101291.1.1.75
		hfs2001c01v1R2lIn10Pres OBJECT-TYPE
			SYNTAX BitFail
			MAX-ACCESS read-only
			STATUS current
			DESCRIPTION
				"R2L IN channel 10 fail"
		::= { hfs2001c01v1Entry 75 }

		-- 1.3.6.1.4.1.10106.3.101291.1.1.77
		hfs2001c01v1R2lIn11Pres OBJECT-TYPE
			SYNTAX BitFail
			MAX-ACCESS read-only
			STATUS current
			DESCRIPTION
				"R2L IN channel 11 fail"
		::= { hfs2001c01v1Entry 77 }

		-- 1.3.6.1.4.1.10106.3.101291.1.1.79
		hfs2001c01v1R2lIn12Pres OBJECT-TYPE
			SYNTAX BitFail
			MAX-ACCESS read-only
			STATUS current
			DESCRIPTION
				"R2L IN channel 12 fail"
		::= { hfs2001c01v1Entry 79 }

		-- 1.3.6.1.4.1.10106.3.101291.1.1.81
		hfs2001c01v1R2lIn13Pres OBJECT-TYPE
			SYNTAX BitFail
			MAX-ACCESS read-only
			STATUS current
			DESCRIPTION
				"R2L IN channel 13 fail"
		::= { hfs2001c01v1Entry 81 }

		-- 1.3.6.1.4.1.10106.3.101291.1.1.83
		hfs2001c01v1R2lIn14Pres OBJECT-TYPE
			SYNTAX BitFail
			MAX-ACCESS read-only
			STATUS current
			DESCRIPTION
				"R2L IN channel 14 fail"
		::= { hfs2001c01v1Entry 83 }

		-- 1.3.6.1.4.1.10106.3.101291.1.1.85
		hfs2001c01v1R2lIn15Pres OBJECT-TYPE
			SYNTAX BitFail
			MAX-ACCESS read-only
			STATUS current
			DESCRIPTION
				"R2L IN channel 15 fail"
		::= { hfs2001c01v1Entry 85 }

		-- 1.3.6.1.4.1.10106.3.101291.1.1.87
		hfs2001c01v1R2lIn16Pres OBJECT-TYPE
			SYNTAX BitFail
			MAX-ACCESS read-only
			STATUS current
			DESCRIPTION
				"R2L IN channel 16 fail"
		::= { hfs2001c01v1Entry 87 }

		-- 1.3.6.1.4.1.10106.3.101291.1.1.89
		hfs2001c01v1SerialNo OBJECT-TYPE
			SYNTAX SerialNo
			MAX-ACCESS read-only
			STATUS current
			DESCRIPTION
				"Serial number"
		::= { hfs2001c01v1Entry 89 }

		-- 1.3.6.1.4.1.10106.3.586701
		gps3003c01v1 OBJECT IDENTIFIER ::= { albalaProducts 586701 }

		-- 1.3.6.1.4.1.10106.3.586701.1
		gps3003c01v1Table  OBJECT-TYPE
			SYNTAX SEQUENCE OF Gps3003c01v1Entry
			MAX-ACCESS not-accessible
			STATUS current
			DESCRIPTION
				"Module  GPS3003C01V1 Table"
			::= { gps3003c01v1 1 }

		-- 1.3.6.1.4.1.10106.3.586701.1.1
		gps3003c01v1Entry  OBJECT-TYPE
			SYNTAX Gps3003c01v1Entry
			MAX-ACCESS not-accessible
			STATUS current
			DESCRIPTION
				"Module GPS3003C01V1 Entry"
			INDEX { gps3003c01v1Index }
			::= { gps3003c01v1Table 1 }

			Gps3003c01v1Entry ::=
			SEQUENCE {
				gps3003c01v1Index
				ModuleIndex,
				gps3003c01v1SyncMode
				Gps2SyncMode,
				gps3003c01v1PtpSrvEnable
				Bit0No1Yes,
				gps3003c01v1PtpCliEnable
				Bit0No1Yes,
				gps3003c01v1InfoTimePps
				Bit0No1Yes,
				gps3003c01v1PtpDelayAsym
				TimeX1Ns,
				gps3003c01v1HoldoverTout
				GpsHoldovrTime,
				gps3003c01v1CableDelay
				DelayX1Ns,
				gps3003c01v1FTimeDriftEst
				Gps2FrqTimDrf,
				gps3003c01v1FTempDriftEst
				Gps2FrqTemDrf,
				gps3003c01v1Longitude
				AngleDeg1,
				gps3003c01v1Latitude
				AngleDeg1,
				gps3003c01v1Altitude
				AltitudeM1,
				gps3003c01v1IpAdd0
				Uint8,
				gps3003c01v1IpAdd1
				Uint8,
				gps3003c01v1IpAdd2
				Uint8,
				gps3003c01v1IpAdd3
				Uint8,
				gps3003c01v1IpMask0
				Uint8,
				gps3003c01v1IpMask1
				Uint8,
				gps3003c01v1IpMask2
				Uint8,
				gps3003c01v1IpMask3
				Uint8,
				gps3003c01v1IpGway0
				Uint8,
				gps3003c01v1IpGway1
				Uint8,
				gps3003c01v1IpGway2
				Uint8,
				gps3003c01v1IpGway3
				Uint8,
				gps3003c01v1Profile
				PtpProfile,
				gps3003c01v1DelayMechanism
				PtpDelayMech,
				gps3003c01v1Priority1
				Uint8,
				gps3003c01v1Priority2
				Uint8,
				gps3003c01v1DomainNumber
				Uint8,
				gps3003c01v1LogAnnounceInt
				PtpInterval,
				gps3003c01v1LogSyncInt
				PtpInterval,
				gps3003c01v1LogMinDRInt
				PtpInterval,
				gps3003c01v1LogMinPdRInt
				PtpInterval,
				gps3003c01v1AnnounceRTout
				Uint4,
				gps3003c01v1ClockClass
				Uint8,
				gps3003c01v1PtpState
				PtpState,
				gps3003c01v1GnssLos
				BitFail,
				gps3003c01v1GnssLosTrapEnable
				AlarmEnable,
				gps3003c01v1GnssPpsLos
				BitFail,
				gps3003c01v1GnssPpsLosTrapEnable
				AlarmEnable,
				gps3003c01v1GnssUnlock
				BitFail,
				gps3003c01v1GnssUnlockTrapEnable
				AlarmEnable,
				gps3003c01v1GnssPpsErr
				BitFail,
				gps3003c01v1GnssPpsErrTrapEnable
				AlarmEnable,
				gps3003c01v1PtpLos
				BitFail,
				gps3003c01v1PtpLosTrapEnable
				AlarmEnable,
				gps3003c01v1PtpPpsLos
				BitFail,
				gps3003c01v1PtpPpsLosTrapEnable
				AlarmEnable,
				gps3003c01v1PtpUnlock
				BitFail,
				gps3003c01v1PtpUnlockTrapEnable
				AlarmEnable,
				gps3003c01v1PtpPpsErr
				BitFail,
				gps3003c01v1PtpPpsErrTrapEnable
				AlarmEnable,
				gps3003c01v1SyncState
				Gps2SyncState,
				gps3003c01v1SyncStateTrapEnable
				AlarmEnable,
				gps3003c01v1ValidPps
				Bit0No1Yes,
				gps3003c01v1ValidPpsTrapEnable
				AlarmEnable,
				gps3003c01v1ModuleActive
				Bit0No1Yes,
				gps3003c01v1ModuleActiveTrapEnable
				AlarmEnable,
				gps3003c01v1RedSyncState
				Gps2SyncState,
				gps3003c01v1RedSyncStateTrapEnable
				AlarmEnable,
				gps3003c01v1RedModule
				Bit0No1Yes,
				gps3003c01v1RedModuleTrapEnable
				AlarmEnable,
				gps3003c01v1FixMode
				Gps2FixMode,
				gps3003c01v1FixModeTrapEnable
				AlarmEnable,
				gps3003c01v1DiffMode
				Bit0No1Yes,
				gps3003c01v1NumUsedSats
				Uint8,
				gps3003c01v1CN0Max
				LevelDbHz,
				gps3003c01v1PositionAcc
				AltitudeM1,
				gps3003c01v1TimTosOffset
				TimeX1Ns,
				gps3003c01v1SurveyTout
				TimeS2,
				gps3003c01v1HoldoverTime
				GpsHoldovrTime,
				gps3003c01v1PowerStat
				Bit0Ok1Fail,
				gps3003c01v1PowerStatTrapEnable
				AlarmEnable,
				gps3003c01v1AntennaStat
				GpsAntenaStat,
				gps3003c01v1AntennaStatTrapEnable
				AlarmEnable,
				gps3003c01v1EthLink
				Bit0No1Yes,
				gps3003c01v1EthLinkTrapEnable
				AlarmEnable,
				gps3003c01v1AdjustingFreq
				Bit0No1Yes,
				gps3003c01v1OcxoWarInProg
				Bit0No1Yes,
				gps3003c01v1OnePpsStat
				Bit0Ina1Act,
				gps3003c01v1OnePpsStatTrapEnable
				AlarmEnable,
				gps3003c01v1OnePps
				BitPps,
				gps3003c01v1GnssDelay
				TimeX1p25Ns,
				gps3003c01v1PtpDelay
				TimeX1p25Ns,
				gps3003c01v1SerialNo
				SerialNo,
				gps3003c01v1GnssModVer
				UbloxF9tVer,
				gps3003c01v1IpNtpSrv0
				Uint8,
				gps3003c01v1IpNtpSrv1
				Uint8,
				gps3003c01v1IpNtpSrv2
				Uint8,
				gps3003c01v1IpNtpSrv3
				Uint8,
				gps3003c01v1TimeDateOk
				BitFailN
			 }

		-- 1.3.6.1.4.1.10106.3.101291.1.1.1
		gps3003c01v1Index OBJECT-TYPE
			SYNTAX ModuleIndex
			MAX-ACCESS read-only
			STATUS current
			DESCRIPTION
				"Index of GPS3003C01V1 Table"
		::= { gps3003c01v1Entry 1 }

		-- 1.3.6.1.4.1.10106.3.101291.1.1.3
		gps3003c01v1SyncMode OBJECT-TYPE
			SYNTAX Gps2SyncMode
			MAX-ACCESS read-write
			STATUS current
			DESCRIPTION
				"Allows selecting the synchronization mode"
		::= { gps3003c01v1Entry 3 }

		-- 1.3.6.1.4.1.10106.3.101291.1.1.5
		gps3003c01v1PtpSrvEnable OBJECT-TYPE
			SYNTAX Bit0No1Yes
			MAX-ACCESS read-write
			STATUS current
			DESCRIPTION
				"Allows enabling the PTP server when Sync mode is GNSS"
		::= { gps3003c01v1Entry 5 }

		-- 1.3.6.1.4.1.10106.3.101291.1.1.7
		gps3003c01v1PtpCliEnable OBJECT-TYPE
			SYNTAX Bit0No1Yes
			MAX-ACCESS read-write
			STATUS current
			DESCRIPTION
				"Allows enabling the PTP client for logging when Sync mode is GNSS"
		::= { gps3003c01v1Entry 7 }

		-- 1.3.6.1.4.1.10106.3.101291.1.1.9
		gps3003c01v1InfoTimePps OBJECT-TYPE
			SYNTAX Bit0No1Yes
			MAX-ACCESS read-write
			STATUS current
			DESCRIPTION
				"Allows embedding PTP timestamp in 1 PPS signal"
		::= { gps3003c01v1Entry 9 }

		-- 1.3.6.1.4.1.10106.3.101291.1.1.11
		gps3003c01v1PtpDelayAsym OBJECT-TYPE
			SYNTAX TimeX1Ns
			MAX-ACCESS read-write
			STATUS current
			DESCRIPTION
				"Allows compensating the PTP delay asymmetry"
		::= { gps3003c01v1Entry 11 }

		-- 1.3.6.1.4.1.10106.3.101291.1.1.13
		gps3003c01v1HoldoverTout OBJECT-TYPE
			SYNTAX GpsHoldovrTime
			MAX-ACCESS read-write
			STATUS current
			DESCRIPTION
				"Allows selecting the maximum holdover time"
		::= { gps3003c01v1Entry 13 }

		-- 1.3.6.1.4.1.10106.3.101291.1.1.15
		gps3003c01v1CableDelay OBJECT-TYPE
			SYNTAX DelayX1Ns
			MAX-ACCESS read-write
			STATUS current
			DESCRIPTION
				"Allows compensating the antenna cable delay"
		::= { gps3003c01v1Entry 15 }

		-- 1.3.6.1.4.1.10106.3.101291.1.1.17
		gps3003c01v1FTimeDriftEst OBJECT-TYPE
			SYNTAX Gps2FrqTimDrf
			MAX-ACCESS read-only
			STATUS current
			DESCRIPTION
				"Frequency time drift estimation"
		::= { gps3003c01v1Entry 17 }

		-- 1.3.6.1.4.1.10106.3.101291.1.1.19
		gps3003c01v1FTempDriftEst OBJECT-TYPE
			SYNTAX Gps2FrqTemDrf
			MAX-ACCESS read-only
			STATUS current
			DESCRIPTION
				"Frequency temperature drift estimation"
		::= { gps3003c01v1Entry 19 }

		-- 1.3.6.1.4.1.10106.3.101291.1.1.21
		gps3003c01v1Longitude OBJECT-TYPE
			SYNTAX AngleDeg1
			MAX-ACCESS read-only
			STATUS current
			DESCRIPTION
				"GNSS receiver reported longitude"
		::= { gps3003c01v1Entry 21 }

		-- 1.3.6.1.4.1.10106.3.101291.1.1.23
		gps3003c01v1Latitude OBJECT-TYPE
			SYNTAX AngleDeg1
			MAX-ACCESS read-only
			STATUS current
			DESCRIPTION
				"GNSS receiver reported latitude"
		::= { gps3003c01v1Entry 23 }

		-- 1.3.6.1.4.1.10106.3.101291.1.1.25
		gps3003c01v1Altitude OBJECT-TYPE
			SYNTAX AltitudeM1
			MAX-ACCESS read-only
			STATUS current
			DESCRIPTION
				"GNSS receiver reported altitude"
		::= { gps3003c01v1Entry 25 }

		-- 1.3.6.1.4.1.10106.3.101291.1.1.27
		gps3003c01v1IpAdd0 OBJECT-TYPE
			SYNTAX Uint8
			MAX-ACCESS read-write
			STATUS current
			DESCRIPTION
				"Unicast IP address (0)"
		::= { gps3003c01v1Entry 27 }

		-- 1.3.6.1.4.1.10106.3.101291.1.1.29
		gps3003c01v1IpAdd1 OBJECT-TYPE
			SYNTAX Uint8
			MAX-ACCESS read-write
			STATUS current
			DESCRIPTION
				"Unicast IP address (1)"
		::= { gps3003c01v1Entry 29 }

		-- 1.3.6.1.4.1.10106.3.101291.1.1.31
		gps3003c01v1IpAdd2 OBJECT-TYPE
			SYNTAX Uint8
			MAX-ACCESS read-write
			STATUS current
			DESCRIPTION
				"Unicast IP address (2)"
		::= { gps3003c01v1Entry 31 }

		-- 1.3.6.1.4.1.10106.3.101291.1.1.33
		gps3003c01v1IpAdd3 OBJECT-TYPE
			SYNTAX Uint8
			MAX-ACCESS read-write
			STATUS current
			DESCRIPTION
				"Unicast IP address (3)"
		::= { gps3003c01v1Entry 33 }

		-- 1.3.6.1.4.1.10106.3.101291.1.1.35
		gps3003c01v1IpMask0 OBJECT-TYPE
			SYNTAX Uint8
			MAX-ACCESS read-write
			STATUS current
			DESCRIPTION
				"IP mask (0)"
		::= { gps3003c01v1Entry 35 }

		-- 1.3.6.1.4.1.10106.3.101291.1.1.37
		gps3003c01v1IpMask1 OBJECT-TYPE
			SYNTAX Uint8
			MAX-ACCESS read-write
			STATUS current
			DESCRIPTION
				"IP mask (1)"
		::= { gps3003c01v1Entry 37 }

		-- 1.3.6.1.4.1.10106.3.101291.1.1.39
		gps3003c01v1IpMask2 OBJECT-TYPE
			SYNTAX Uint8
			MAX-ACCESS read-write
			STATUS current
			DESCRIPTION
				"IP mask (2)"
		::= { gps3003c01v1Entry 39 }

		-- 1.3.6.1.4.1.10106.3.101291.1.1.41
		gps3003c01v1IpMask3 OBJECT-TYPE
			SYNTAX Uint8
			MAX-ACCESS read-write
			STATUS current
			DESCRIPTION
				"IP mask (3)"
		::= { gps3003c01v1Entry 41 }

		-- 1.3.6.1.4.1.10106.3.101291.1.1.43
		gps3003c01v1IpGway0 OBJECT-TYPE
			SYNTAX Uint8
			MAX-ACCESS read-write
			STATUS current
			DESCRIPTION
				"Gateway IP address (0)"
		::= { gps3003c01v1Entry 43 }

		-- 1.3.6.1.4.1.10106.3.101291.1.1.45
		gps3003c01v1IpGway1 OBJECT-TYPE
			SYNTAX Uint8
			MAX-ACCESS read-write
			STATUS current
			DESCRIPTION
				"Gateway IP address (1)"
		::= { gps3003c01v1Entry 45 }

		-- 1.3.6.1.4.1.10106.3.101291.1.1.47
		gps3003c01v1IpGway2 OBJECT-TYPE
			SYNTAX Uint8
			MAX-ACCESS read-write
			STATUS current
			DESCRIPTION
				"Gateway IP address (2)"
		::= { gps3003c01v1Entry 47 }

		-- 1.3.6.1.4.1.10106.3.101291.1.1.49
		gps3003c01v1IpGway3 OBJECT-TYPE
			SYNTAX Uint8
			MAX-ACCESS read-write
			STATUS current
			DESCRIPTION
				"Gateway IP address (3)"
		::= { gps3003c01v1Entry 49 }

		-- 1.3.6.1.4.1.10106.3.101291.1.1.51
		gps3003c01v1Profile OBJECT-TYPE
			SYNTAX PtpProfile
			MAX-ACCESS read-write
			STATUS current
			DESCRIPTION
				"Allows loading default values of a PTP profile"
		::= { gps3003c01v1Entry 51 }

		-- 1.3.6.1.4.1.10106.3.101291.1.1.53
		gps3003c01v1DelayMechanism OBJECT-TYPE
			SYNTAX PtpDelayMech
			MAX-ACCESS read-write
			STATUS current
			DESCRIPTION
				"Allows selecting the delay mechanism"
		::= { gps3003c01v1Entry 53 }

		-- 1.3.6.1.4.1.10106.3.101291.1.1.55
		gps3003c01v1Priority1 OBJECT-TYPE
			SYNTAX Uint8
			MAX-ACCESS read-write
			STATUS current
			DESCRIPTION
				"Allows selecting the Priority1 attribute of the local clock. It is used in the best master selection algorithm"
		::= { gps3003c01v1Entry 55 }

		-- 1.3.6.1.4.1.10106.3.101291.1.1.57
		gps3003c01v1Priority2 OBJECT-TYPE
			SYNTAX Uint8
			MAX-ACCESS read-write
			STATUS current
			DESCRIPTION
				"Allows selecting the Priority2 attribute of the local clock. It is used in the best master selection algorithm"
		::= { gps3003c01v1Entry 57 }

		-- 1.3.6.1.4.1.10106.3.101291.1.1.59
		gps3003c01v1DomainNumber OBJECT-TYPE
			SYNTAX Uint8
			MAX-ACCESS read-write
			STATUS current
			DESCRIPTION
				"Allows selecting the Domanin number attribute of the local clock"
		::= { gps3003c01v1Entry 59 }

		-- 1.3.6.1.4.1.10106.3.101291.1.1.61
		gps3003c01v1LogAnnounceInt OBJECT-TYPE
			SYNTAX PtpInterval
			MAX-ACCESS read-write
			STATUS current
			DESCRIPTION
				"Allows selecting the mean interval between Announce messages"
		::= { gps3003c01v1Entry 61 }

		-- 1.3.6.1.4.1.10106.3.101291.1.1.63
		gps3003c01v1LogSyncInt OBJECT-TYPE
			SYNTAX PtpInterval
			MAX-ACCESS read-write
			STATUS current
			DESCRIPTION
				"Allows selecting the mean interval between Sync messages"
		::= { gps3003c01v1Entry 63 }

		-- 1.3.6.1.4.1.10106.3.101291.1.1.65
		gps3003c01v1LogMinDRInt OBJECT-TYPE
			SYNTAX PtpInterval
			MAX-ACCESS read-write
			STATUS current
			DESCRIPTION
				"Allows selecting the minimum mean interval between Delay_Req messages"
		::= { gps3003c01v1Entry 65 }

		-- 1.3.6.1.4.1.10106.3.101291.1.1.67
		gps3003c01v1LogMinPdRInt OBJECT-TYPE
			SYNTAX PtpInterval
			MAX-ACCESS read-write
			STATUS current
			DESCRIPTION
				"Allows selecting the minimum mean interval between Pdelay_Req messages"
		::= { gps3003c01v1Entry 67 }

		-- 1.3.6.1.4.1.10106.3.101291.1.1.69
		gps3003c01v1AnnounceRTout OBJECT-TYPE
			SYNTAX Uint4
			MAX-ACCESS read-write
			STATUS current
			DESCRIPTION
				"Allows selecting the number of missed Announce messages before the last Announce messages expires"
		::= { gps3003c01v1Entry 69 }

		-- 1.3.6.1.4.1.10106.3.101291.1.1.71
		gps3003c01v1ClockClass OBJECT-TYPE
			SYNTAX Uint8
			MAX-ACCESS read-only
			STATUS current
			DESCRIPTION
				"Indicates the value of the ClockClass attribute of the local clock"
		::= { gps3003c01v1Entry 71 }

		-- 1.3.6.1.4.1.10106.3.101291.1.1.73
		gps3003c01v1PtpState OBJECT-TYPE
			SYNTAX PtpState
			MAX-ACCESS read-only
			STATUS current
			DESCRIPTION
				"Indicates the PTP state"
		::= { gps3003c01v1Entry 73 }

		-- 1.3.6.1.4.1.10106.3.101291.1.1.75
		gps3003c01v1GnssLos OBJECT-TYPE
			SYNTAX BitFail
			MAX-ACCESS read-only
			STATUS current
			DESCRIPTION
				"GNSS loss of signal. To be cleared it has to be for 30 s in in 3D-FIX or Time mode"
		::= { gps3003c01v1Entry 75 }

		-- 1.3.6.1.4.1.10106.3.101291.1.1.76
		gps3003c01v1GnssLosTrapEnable OBJECT-TYPE
			SYNTAX AlarmEnable
			MAX-ACCESS read-write
			STATUS current
			DESCRIPTION
				"GNSS loss of signal. To be cleared it has to be for 30 s in in 3D-FIX or Time mode Trap Enable"
		::= { gps3003c01v1Entry 76 }

		-- 1.3.6.1.4.1.10106.3.101291.1.1.77
		gps3003c01v1GnssPpsLos OBJECT-TYPE
			SYNTAX BitFail
			MAX-ACCESS read-only
			STATUS current
			DESCRIPTION
				"GNSS loss of PPS. It is cleared when the error of the PPS delivered by GNSS module is less than 5 ns. It is set when the delay is greater than 50 ns"
		::= { gps3003c01v1Entry 77 }

		-- 1.3.6.1.4.1.10106.3.101291.1.1.78
		gps3003c01v1GnssPpsLosTrapEnable OBJECT-TYPE
			SYNTAX AlarmEnable
			MAX-ACCESS read-write
			STATUS current
			DESCRIPTION
				"GNSS loss of PPS. It is cleared when the error of the PPS delivered by GNSS module is less than 5 ns. It is set when the delay is greater than 50 ns Trap Enable"
		::= { gps3003c01v1Entry 78 }

		-- 1.3.6.1.4.1.10106.3.101291.1.1.79
		gps3003c01v1GnssUnlock OBJECT-TYPE
			SYNTAX BitFail
			MAX-ACCESS read-only
			STATUS current
			DESCRIPTION
				"GNSS PPS unlock. It is cleared when the error of the output PPS is less than 10 ns. It is set when the error is greater than 100 ns."
		::= { gps3003c01v1Entry 79 }

		-- 1.3.6.1.4.1.10106.3.101291.1.1.80
		gps3003c01v1GnssUnlockTrapEnable OBJECT-TYPE
			SYNTAX AlarmEnable
			MAX-ACCESS read-write
			STATUS current
			DESCRIPTION
				"GNSS PPS unlock. It is cleared when the error of the output PPS is less than 10 ns. It is set when the error is greater than 100 ns. Trap Enable"
		::= { gps3003c01v1Entry 80 }

		-- 1.3.6.1.4.1.10106.3.101291.1.1.81
		gps3003c01v1GnssPpsErr OBJECT-TYPE
			SYNTAX BitFail
			MAX-ACCESS read-only
			STATUS current
			DESCRIPTION
				"GNSS pulse error. It is cleared when the error of the output PPS is less than the value specified in 'GNSS valid PPS margin'. It is set when the error is greater than this value."
		::= { gps3003c01v1Entry 81 }

		-- 1.3.6.1.4.1.10106.3.101291.1.1.82
		gps3003c01v1GnssPpsErrTrapEnable OBJECT-TYPE
			SYNTAX AlarmEnable
			MAX-ACCESS read-write
			STATUS current
			DESCRIPTION
				"GNSS pulse error. It is cleared when the error of the output PPS is less than the value specified in 'GNSS valid PPS margin'. It is set when the error is greater than this value. Trap Enable"
		::= { gps3003c01v1Entry 82 }

		-- 1.3.6.1.4.1.10106.3.101291.1.1.83
		gps3003c01v1PtpLos OBJECT-TYPE
			SYNTAX BitFail
			MAX-ACCESS read-only
			STATUS current
			DESCRIPTION
				"PTP loss of signal.It is cleared when the PTP module is in Slave or Uncalibrated mode"
		::= { gps3003c01v1Entry 83 }

		-- 1.3.6.1.4.1.10106.3.101291.1.1.84
		gps3003c01v1PtpLosTrapEnable OBJECT-TYPE
			SYNTAX AlarmEnable
			MAX-ACCESS read-write
			STATUS current
			DESCRIPTION
				"PTP loss of signal.It is cleared when the PTP module is in Slave or Uncalibrated mode Trap Enable"
		::= { gps3003c01v1Entry 84 }

		-- 1.3.6.1.4.1.10106.3.101291.1.1.85
		gps3003c01v1PtpPpsLos OBJECT-TYPE
			SYNTAX BitFail
			MAX-ACCESS read-only
			STATUS current
			DESCRIPTION
				"PTP loss of PPS. It is cleared after 30 s receiving a valid PPS from PTP module"
		::= { gps3003c01v1Entry 85 }

		-- 1.3.6.1.4.1.10106.3.101291.1.1.86
		gps3003c01v1PtpPpsLosTrapEnable OBJECT-TYPE
			SYNTAX AlarmEnable
			MAX-ACCESS read-write
			STATUS current
			DESCRIPTION
				"PTP loss of PPS. It is cleared after 30 s receiving a valid PPS from PTP module Trap Enable"
		::= { gps3003c01v1Entry 86 }

		-- 1.3.6.1.4.1.10106.3.101291.1.1.87
		gps3003c01v1PtpUnlock OBJECT-TYPE
			SYNTAX BitFail
			MAX-ACCESS read-only
			STATUS current
			DESCRIPTION
				"PTP PPS unlock. It is cleared when the error of the output PPS is less than 25 ns. It is set when the error is greater than 250 ns."
		::= { gps3003c01v1Entry 87 }

		-- 1.3.6.1.4.1.10106.3.101291.1.1.88
		gps3003c01v1PtpUnlockTrapEnable OBJECT-TYPE
			SYNTAX AlarmEnable
			MAX-ACCESS read-write
			STATUS current
			DESCRIPTION
				"PTP PPS unlock. It is cleared when the error of the output PPS is less than 25 ns. It is set when the error is greater than 250 ns. Trap Enable"
		::= { gps3003c01v1Entry 88 }

		-- 1.3.6.1.4.1.10106.3.101291.1.1.89
		gps3003c01v1PtpPpsErr OBJECT-TYPE
			SYNTAX BitFail
			MAX-ACCESS read-only
			STATUS current
			DESCRIPTION
				"PTP PPS error. It is cleared when the error of the output PPS is less than the value specified in 'PTP valid PPS margin'. It is set when the error is greater than this value."
		::= { gps3003c01v1Entry 89 }

		-- 1.3.6.1.4.1.10106.3.101291.1.1.90
		gps3003c01v1PtpPpsErrTrapEnable OBJECT-TYPE
			SYNTAX AlarmEnable
			MAX-ACCESS read-write
			STATUS current
			DESCRIPTION
				"PTP PPS error. It is cleared when the error of the output PPS is less than the value specified in 'PTP valid PPS margin'. It is set when the error is greater than this value. Trap Enable"
		::= { gps3003c01v1Entry 90 }

		-- 1.3.6.1.4.1.10106.3.101291.1.1.91
		gps3003c01v1SyncState OBJECT-TYPE
			SYNTAX Gps2SyncState
			MAX-ACCESS read-only
			STATUS current
			DESCRIPTION
				"Indicates the synchronization state"
		::= { gps3003c01v1Entry 91 }

		-- 1.3.6.1.4.1.10106.3.101291.1.1.92
		gps3003c01v1SyncStateTrapEnable OBJECT-TYPE
			SYNTAX AlarmEnable
			MAX-ACCESS read-write
			STATUS current
			DESCRIPTION
				"Indicates the synchronization state Trap Enable"
		::= { gps3003c01v1Entry 92 }

		-- 1.3.6.1.4.1.10106.3.101291.1.1.93
		gps3003c01v1ValidPps OBJECT-TYPE
			SYNTAX Bit0No1Yes
			MAX-ACCESS read-only
			STATUS current
			DESCRIPTION
				"Indicates that the internally generated PPS signal has been phase aligned with an external reference (GNSS or PTP)"
		::= { gps3003c01v1Entry 93 }

		-- 1.3.6.1.4.1.10106.3.101291.1.1.94
		gps3003c01v1ValidPpsTrapEnable OBJECT-TYPE
			SYNTAX AlarmEnable
			MAX-ACCESS read-write
			STATUS current
			DESCRIPTION
				"Indicates that the internally generated PPS signal has been phase aligned with an external reference (GNSS or PTP) Trap Enable"
		::= { gps3003c01v1Entry 94 }

		-- 1.3.6.1.4.1.10106.3.101291.1.1.95
		gps3003c01v1ModuleActive OBJECT-TYPE
			SYNTAX Bit0No1Yes
			MAX-ACCESS read-only
			STATUS current
			DESCRIPTION
				"Indicates that this module is the one that provides the reference signals"
		::= { gps3003c01v1Entry 95 }

		-- 1.3.6.1.4.1.10106.3.101291.1.1.96
		gps3003c01v1ModuleActiveTrapEnable OBJECT-TYPE
			SYNTAX AlarmEnable
			MAX-ACCESS read-write
			STATUS current
			DESCRIPTION
				"Indicates that this module is the one that provides the reference signals Trap Enable"
		::= { gps3003c01v1Entry 96 }

		-- 1.3.6.1.4.1.10106.3.101291.1.1.97
		gps3003c01v1RedSyncState OBJECT-TYPE
			SYNTAX Gps2SyncState
			MAX-ACCESS read-only
			STATUS current
			DESCRIPTION
				"Indicates the redundant module's synchronization state"
		::= { gps3003c01v1Entry 97 }

		-- 1.3.6.1.4.1.10106.3.101291.1.1.98
		gps3003c01v1RedSyncStateTrapEnable OBJECT-TYPE
			SYNTAX AlarmEnable
			MAX-ACCESS read-write
			STATUS current
			DESCRIPTION
				"Indicates the redundant module's synchronization state Trap Enable"
		::= { gps3003c01v1Entry 98 }

		-- 1.3.6.1.4.1.10106.3.101291.1.1.99
		gps3003c01v1RedModule OBJECT-TYPE
			SYNTAX Bit0No1Yes
			MAX-ACCESS read-only
			STATUS current
			DESCRIPTION
				"Indicates if the redundant module is present"
		::= { gps3003c01v1Entry 99 }

		-- 1.3.6.1.4.1.10106.3.101291.1.1.100
		gps3003c01v1RedModuleTrapEnable OBJECT-TYPE
			SYNTAX AlarmEnable
			MAX-ACCESS read-write
			STATUS current
			DESCRIPTION
				"Indicates if the redundant module is present Trap Enable"
		::= { gps3003c01v1Entry 100 }

		-- 1.3.6.1.4.1.10106.3.101291.1.1.101
		gps3003c01v1FixMode OBJECT-TYPE
			SYNTAX Gps2FixMode
			MAX-ACCESS read-only
			STATUS current
			DESCRIPTION
				"GNSS receiver module satellite tracking mode"
		::= { gps3003c01v1Entry 101 }

		-- 1.3.6.1.4.1.10106.3.101291.1.1.102
		gps3003c01v1FixModeTrapEnable OBJECT-TYPE
			SYNTAX AlarmEnable
			MAX-ACCESS read-write
			STATUS current
			DESCRIPTION
				"GNSS receiver module satellite tracking mode Trap Enable"
		::= { gps3003c01v1Entry 102 }

		-- 1.3.6.1.4.1.10106.3.101291.1.1.103
		gps3003c01v1DiffMode OBJECT-TYPE
			SYNTAX Bit0No1Yes
			MAX-ACCESS read-only
			STATUS current
			DESCRIPTION
				"GNSS receiver receives correction data and uses them to improve provided solution"
		::= { gps3003c01v1Entry 103 }

		-- 1.3.6.1.4.1.10106.3.101291.1.1.105
		gps3003c01v1NumUsedSats OBJECT-TYPE
			SYNTAX Uint8
			MAX-ACCESS read-only
			STATUS current
			DESCRIPTION
				"Number of GNSS used in current fix"
		::= { gps3003c01v1Entry 105 }

		-- 1.3.6.1.4.1.10106.3.101291.1.1.107
		gps3003c01v1CN0Max OBJECT-TYPE
			SYNTAX LevelDbHz
			MAX-ACCESS read-only
			STATUS current
			DESCRIPTION
				"Estimated carrier to noise ratio for the best satellite in tracking"
		::= { gps3003c01v1Entry 107 }

		-- 1.3.6.1.4.1.10106.3.101291.1.1.109
		gps3003c01v1PositionAcc OBJECT-TYPE
			SYNTAX AltitudeM1
			MAX-ACCESS read-only
			STATUS current
			DESCRIPTION
				"Estimated position accuracy"
		::= { gps3003c01v1Entry 109 }

		-- 1.3.6.1.4.1.10106.3.101291.1.1.111
		gps3003c01v1TimTosOffset OBJECT-TYPE
			SYNTAX TimeX1Ns
			MAX-ACCESS read-only
			STATUS current
			DESCRIPTION
				"Estimated GNSS module PPS error"
		::= { gps3003c01v1Entry 111 }

		-- 1.3.6.1.4.1.10106.3.101291.1.1.113
		gps3003c01v1SurveyTout OBJECT-TYPE
			SYNTAX TimeS2
			MAX-ACCESS read-only
			STATUS current
			DESCRIPTION
				"Time to exit Survey-in"
		::= { gps3003c01v1Entry 113 }

		-- 1.3.6.1.4.1.10106.3.101291.1.1.115
		gps3003c01v1HoldoverTime OBJECT-TYPE
			SYNTAX GpsHoldovrTime
			MAX-ACCESS read-only
			STATUS current
			DESCRIPTION
				"Holdover time"
		::= { gps3003c01v1Entry 115 }

		-- 1.3.6.1.4.1.10106.3.101291.1.1.117
		gps3003c01v1PowerStat OBJECT-TYPE
			SYNTAX Bit0Ok1Fail
			MAX-ACCESS read-only
			STATUS current
			DESCRIPTION
				"Indicates the power supply status"
		::= { gps3003c01v1Entry 117 }

		-- 1.3.6.1.4.1.10106.3.101291.1.1.118
		gps3003c01v1PowerStatTrapEnable OBJECT-TYPE
			SYNTAX AlarmEnable
			MAX-ACCESS read-write
			STATUS current
			DESCRIPTION
				"Indicates the power supply status Trap Enable"
		::= { gps3003c01v1Entry 118 }

		-- 1.3.6.1.4.1.10106.3.101291.1.1.119
		gps3003c01v1AntennaStat OBJECT-TYPE
			SYNTAX GpsAntenaStat
			MAX-ACCESS read-only
			STATUS current
			DESCRIPTION
				"Indicates the antenna connection status"
		::= { gps3003c01v1Entry 119 }

		-- 1.3.6.1.4.1.10106.3.101291.1.1.120
		gps3003c01v1AntennaStatTrapEnable OBJECT-TYPE
			SYNTAX AlarmEnable
			MAX-ACCESS read-write
			STATUS current
			DESCRIPTION
				"Indicates the antenna connection status Trap Enable"
		::= { gps3003c01v1Entry 120 }

		-- 1.3.6.1.4.1.10106.3.101291.1.1.121
		gps3003c01v1EthLink OBJECT-TYPE
			SYNTAX Bit0No1Yes
			MAX-ACCESS read-only
			STATUS current
			DESCRIPTION
				"Indicates that the Ethernet link is OK"
		::= { gps3003c01v1Entry 121 }

		-- 1.3.6.1.4.1.10106.3.101291.1.1.122
		gps3003c01v1EthLinkTrapEnable OBJECT-TYPE
			SYNTAX AlarmEnable
			MAX-ACCESS read-write
			STATUS current
			DESCRIPTION
				"Indicates that the Ethernet link is OK Trap Enable"
		::= { gps3003c01v1Entry 122 }

		-- 1.3.6.1.4.1.10106.3.101291.1.1.123
		gps3003c01v1AdjustingFreq OBJECT-TYPE
			SYNTAX Bit0No1Yes
			MAX-ACCESS read-only
			STATUS current
			DESCRIPTION
				"Indicates that the module is adjusting the frequency"
		::= { gps3003c01v1Entry 123 }

		-- 1.3.6.1.4.1.10106.3.101291.1.1.125
		gps3003c01v1OcxoWarInProg OBJECT-TYPE
			SYNTAX Bit0No1Yes
			MAX-ACCESS read-only
			STATUS current
			DESCRIPTION
				"Indicates that the OCXO warming is in progress"
		::= { gps3003c01v1Entry 125 }

		-- 1.3.6.1.4.1.10106.3.101291.1.1.127
		gps3003c01v1OnePpsStat OBJECT-TYPE
			SYNTAX Bit0Ina1Act
			MAX-ACCESS read-only
			STATUS current
			DESCRIPTION
				"Indicates that the module is delivering a valid PPS"
		::= { gps3003c01v1Entry 127 }

		-- 1.3.6.1.4.1.10106.3.101291.1.1.128
		gps3003c01v1OnePpsStatTrapEnable OBJECT-TYPE
			SYNTAX AlarmEnable
			MAX-ACCESS read-write
			STATUS current
			DESCRIPTION
				"Indicates that the module is delivering a valid PPS Trap Enable"
		::= { gps3003c01v1Entry 128 }

		-- 1.3.6.1.4.1.10106.3.101291.1.1.129
		gps3003c01v1OnePps OBJECT-TYPE
			SYNTAX BitPps
			MAX-ACCESS read-only
			STATUS current
			DESCRIPTION
				"One pulse per second signal"
		::= { gps3003c01v1Entry 129 }

		-- 1.3.6.1.4.1.10106.3.101291.1.1.131
		gps3003c01v1GnssDelay OBJECT-TYPE
			SYNTAX TimeX1p25Ns
			MAX-ACCESS read-only
			STATUS current
			DESCRIPTION
				"PPS delay relative to GNSS"
		::= { gps3003c01v1Entry 131 }

		-- 1.3.6.1.4.1.10106.3.101291.1.1.133
		gps3003c01v1PtpDelay OBJECT-TYPE
			SYNTAX TimeX1p25Ns
			MAX-ACCESS read-only
			STATUS current
			DESCRIPTION
				"PPS delay relative to PTP"
		::= { gps3003c01v1Entry 133 }

		-- 1.3.6.1.4.1.10106.3.101291.1.1.135
		gps3003c01v1SerialNo OBJECT-TYPE
			SYNTAX SerialNo
			MAX-ACCESS read-only
			STATUS current
			DESCRIPTION
				"Serial number"
		::= { gps3003c01v1Entry 135 }

		-- 1.3.6.1.4.1.10106.3.101291.1.1.137
		gps3003c01v1GnssModVer OBJECT-TYPE
			SYNTAX UbloxF9tVer
			MAX-ACCESS read-only
			STATUS current
			DESCRIPTION
				"GNSS module version"
		::= { gps3003c01v1Entry 137 }

		-- 1.3.6.1.4.1.10106.3.101291.1.1.139
		gps3003c01v1IpNtpSrv0 OBJECT-TYPE
			SYNTAX Uint8
			MAX-ACCESS read-write
			STATUS current
			DESCRIPTION
				"NTP server IP address (0)"
		::= { gps3003c01v1Entry 139 }

		-- 1.3.6.1.4.1.10106.3.101291.1.1.141
		gps3003c01v1IpNtpSrv1 OBJECT-TYPE
			SYNTAX Uint8
			MAX-ACCESS read-write
			STATUS current
			DESCRIPTION
				"NTP server IP address (1)"
		::= { gps3003c01v1Entry 141 }

		-- 1.3.6.1.4.1.10106.3.101291.1.1.143
		gps3003c01v1IpNtpSrv2 OBJECT-TYPE
			SYNTAX Uint8
			MAX-ACCESS read-write
			STATUS current
			DESCRIPTION
				"NTP server IP address (2)"
		::= { gps3003c01v1Entry 143 }

		-- 1.3.6.1.4.1.10106.3.101291.1.1.145
		gps3003c01v1IpNtpSrv3 OBJECT-TYPE
			SYNTAX Uint8
			MAX-ACCESS read-write
			STATUS current
			DESCRIPTION
				"NTP server IP address (3)"
		::= { gps3003c01v1Entry 145 }

		-- 1.3.6.1.4.1.10106.3.101291.1.1.147
		gps3003c01v1TimeDateOk OBJECT-TYPE
			SYNTAX BitFailN
			MAX-ACCESS read-only
			STATUS current
			DESCRIPTION
				"Time and date OK"
		::= { gps3003c01v1Entry 147 }

		-- 1.3.6.1.4.1.10106.3.586801
		sem2000c01v1 OBJECT IDENTIFIER ::= { albalaProducts 586801 }

		-- 1.3.6.1.4.1.10106.3.586801.1
		sem2000c01v1Table  OBJECT-TYPE
			SYNTAX SEQUENCE OF Sem2000c01v1Entry
			MAX-ACCESS not-accessible
			STATUS current
			DESCRIPTION
				"Module  SEM2000C01V1 Table"
			::= { sem2000c01v1 1 }

		-- 1.3.6.1.4.1.10106.3.586801.1.1
		sem2000c01v1Entry  OBJECT-TYPE
			SYNTAX Sem2000c01v1Entry
			MAX-ACCESS not-accessible
			STATUS current
			DESCRIPTION
				"Module SEM2000C01V1 Entry"
			INDEX { sem2000c01v1Index }
			::= { sem2000c01v1Table 1 }

			Sem2000c01v1Entry ::=
			SEQUENCE {
				sem2000c01v1Index
				ModuleIndex,
				sem2000c01v1P1EthMode
				EthMode2000,
				sem2000c01v1P2EthMode
				EthMode2000,
				sem2000c01v1PoEthMode
				EthMode2g5,
				sem2000c01v1NoRefQl
				Bit0No1Yes,
				sem2000c01v1SfpPres
				BitFailN,
				sem2000c01v1SfpPresTrapEnable
				AlarmEnable,
				sem2000c01v1SfpFail
				BitFail,
				sem2000c01v1SfpFailTrapEnable
				AlarmEnable,
				sem2000c01v1SfpLos
				BitFail,
				sem2000c01v1SfpLosTrapEnable
				AlarmEnable,
				sem2000c01v1SfpDiagSupport
				BitFailN,
				sem2000c01v1P1Status
				Smc2EthModeSt,
				sem2000c01v1P1StatusTrapEnable
				AlarmEnable,
				sem2000c01v1P2Status
				Smc2EthModeSt,
				sem2000c01v1P2StatusTrapEnable
				AlarmEnable,
				sem2000c01v1PoStatus
				Smc2EthModeSt,
				sem2000c01v1PoStatusTrapEnable
				AlarmEnable,
				sem2000c01v1SfpPower
				OptPowerX2Uw,
				sem2000c01v1SfpTemp
				Temperature0c1,
				sem2000c01v1BusUnlock
				BitFail,
				sem2000c01v1BusUnlockTrapEnable
				AlarmEnable,
				sem2000c01v1BusLos
				BitFail,
				sem2000c01v1BusLosTrapEnable
				AlarmEnable,
				sem2000c01v1SerialNo
				SerialNo
			 }

		-- 1.3.6.1.4.1.10106.3.101291.1.1.1
		sem2000c01v1Index OBJECT-TYPE
			SYNTAX ModuleIndex
			MAX-ACCESS read-only
			STATUS current
			DESCRIPTION
				"Index of SEM2000C01V1 Table"
		::= { sem2000c01v1Entry 1 }

		-- 1.3.6.1.4.1.10106.3.101291.1.1.3
		sem2000c01v1P1EthMode OBJECT-TYPE
			SYNTAX EthMode2000
			MAX-ACCESS read-write
			STATUS current
			DESCRIPTION
				"Ethernet mode in Port 1"
		::= { sem2000c01v1Entry 3 }

		-- 1.3.6.1.4.1.10106.3.101291.1.1.5
		sem2000c01v1P2EthMode OBJECT-TYPE
			SYNTAX EthMode2000
			MAX-ACCESS read-write
			STATUS current
			DESCRIPTION
				"Ethernet mode in Port 2"
		::= { sem2000c01v1Entry 5 }

		-- 1.3.6.1.4.1.10106.3.101291.1.1.7
		sem2000c01v1PoEthMode OBJECT-TYPE
			SYNTAX EthMode2g5
			MAX-ACCESS read-write
			STATUS current
			DESCRIPTION
				"Ethernet mode in Optical port"
		::= { sem2000c01v1Entry 7 }

		-- 1.3.6.1.4.1.10106.3.101291.1.1.9
		sem2000c01v1NoRefQl OBJECT-TYPE
			SYNTAX Bit0No1Yes
			MAX-ACCESS read-write
			STATUS current
			DESCRIPTION
				"Announce 'Do Not Use' Quality Level when reference fails"
		::= { sem2000c01v1Entry 9 }

		-- 1.3.6.1.4.1.10106.3.101291.1.1.11
		sem2000c01v1SfpPres OBJECT-TYPE
			SYNTAX BitFailN
			MAX-ACCESS read-only
			STATUS current
			DESCRIPTION
				"SFP module present"
		::= { sem2000c01v1Entry 11 }

		-- 1.3.6.1.4.1.10106.3.101291.1.1.12
		sem2000c01v1SfpPresTrapEnable OBJECT-TYPE
			SYNTAX AlarmEnable
			MAX-ACCESS read-write
			STATUS current
			DESCRIPTION
				"SFP module present Trap Enable"
		::= { sem2000c01v1Entry 12 }

		-- 1.3.6.1.4.1.10106.3.101291.1.1.13
		sem2000c01v1SfpFail OBJECT-TYPE
			SYNTAX BitFail
			MAX-ACCESS read-only
			STATUS current
			DESCRIPTION
				"Indicates a laser fault"
		::= { sem2000c01v1Entry 13 }

		-- 1.3.6.1.4.1.10106.3.101291.1.1.14
		sem2000c01v1SfpFailTrapEnable OBJECT-TYPE
			SYNTAX AlarmEnable
			MAX-ACCESS read-write
			STATUS current
			DESCRIPTION
				"Indicates a laser fault Trap Enable"
		::= { sem2000c01v1Entry 14 }

		-- 1.3.6.1.4.1.10106.3.101291.1.1.15
		sem2000c01v1SfpLos OBJECT-TYPE
			SYNTAX BitFail
			MAX-ACCESS read-only
			STATUS current
			DESCRIPTION
				"SFP loss of signal"
		::= { sem2000c01v1Entry 15 }

		-- 1.3.6.1.4.1.10106.3.101291.1.1.16
		sem2000c01v1SfpLosTrapEnable OBJECT-TYPE
			SYNTAX AlarmEnable
			MAX-ACCESS read-write
			STATUS current
			DESCRIPTION
				"SFP loss of signal Trap Enable"
		::= { sem2000c01v1Entry 16 }

		-- 1.3.6.1.4.1.10106.3.101291.1.1.17
		sem2000c01v1SfpDiagSupport OBJECT-TYPE
			SYNTAX BitFailN
			MAX-ACCESS read-only
			STATUS current
			DESCRIPTION
				"SFP mod. supports diagnostics"
		::= { sem2000c01v1Entry 17 }

		-- 1.3.6.1.4.1.10106.3.101291.1.1.19
		sem2000c01v1P1Status OBJECT-TYPE
			SYNTAX Smc2EthModeSt
			MAX-ACCESS read-only
			STATUS current
			DESCRIPTION
				"Ethernet connection status in Port 1"
		::= { sem2000c01v1Entry 19 }

		-- 1.3.6.1.4.1.10106.3.101291.1.1.20
		sem2000c01v1P1StatusTrapEnable OBJECT-TYPE
			SYNTAX AlarmEnable
			MAX-ACCESS read-write
			STATUS current
			DESCRIPTION
				"Ethernet connection status in Port 1 Trap Enable"
		::= { sem2000c01v1Entry 20 }

		-- 1.3.6.1.4.1.10106.3.101291.1.1.21
		sem2000c01v1P2Status OBJECT-TYPE
			SYNTAX Smc2EthModeSt
			MAX-ACCESS read-only
			STATUS current
			DESCRIPTION
				"Ethernet connection status in Port 2"
		::= { sem2000c01v1Entry 21 }

		-- 1.3.6.1.4.1.10106.3.101291.1.1.22
		sem2000c01v1P2StatusTrapEnable OBJECT-TYPE
			SYNTAX AlarmEnable
			MAX-ACCESS read-write
			STATUS current
			DESCRIPTION
				"Ethernet connection status in Port 2 Trap Enable"
		::= { sem2000c01v1Entry 22 }

		-- 1.3.6.1.4.1.10106.3.101291.1.1.23
		sem2000c01v1PoStatus OBJECT-TYPE
			SYNTAX Smc2EthModeSt
			MAX-ACCESS read-only
			STATUS current
			DESCRIPTION
				"Ethernet connection status in Optical Port"
		::= { sem2000c01v1Entry 23 }

		-- 1.3.6.1.4.1.10106.3.101291.1.1.24
		sem2000c01v1PoStatusTrapEnable OBJECT-TYPE
			SYNTAX AlarmEnable
			MAX-ACCESS read-write
			STATUS current
			DESCRIPTION
				"Ethernet connection status in Optical Port Trap Enable"
		::= { sem2000c01v1Entry 24 }

		-- 1.3.6.1.4.1.10106.3.101291.1.1.25
		sem2000c01v1SfpPower OBJECT-TYPE
			SYNTAX OptPowerX2Uw
			MAX-ACCESS read-only
			STATUS current
			DESCRIPTION
				"Optical received power"
		::= { sem2000c01v1Entry 25 }

		-- 1.3.6.1.4.1.10106.3.101291.1.1.27
		sem2000c01v1SfpTemp OBJECT-TYPE
			SYNTAX Temperature0c1
			MAX-ACCESS read-only
			STATUS current
			DESCRIPTION
				"SFP module temperatura"
		::= { sem2000c01v1Entry 27 }

		-- 1.3.6.1.4.1.10106.3.101291.1.1.29
		sem2000c01v1BusUnlock OBJECT-TYPE
			SYNTAX BitFail
			MAX-ACCESS read-only
			STATUS current
			DESCRIPTION
				"Module not locked to the 10 MHz signal from bus"
		::= { sem2000c01v1Entry 29 }

		-- 1.3.6.1.4.1.10106.3.101291.1.1.30
		sem2000c01v1BusUnlockTrapEnable OBJECT-TYPE
			SYNTAX AlarmEnable
			MAX-ACCESS read-write
			STATUS current
			DESCRIPTION
				"Module not locked to the 10 MHz signal from bus Trap Enable"
		::= { sem2000c01v1Entry 30 }

		-- 1.3.6.1.4.1.10106.3.101291.1.1.31
		sem2000c01v1BusLos OBJECT-TYPE
			SYNTAX BitFail
			MAX-ACCESS read-only
			STATUS current
			DESCRIPTION
				"10 MHz signal not detected in bus"
		::= { sem2000c01v1Entry 31 }

		-- 1.3.6.1.4.1.10106.3.101291.1.1.32
		sem2000c01v1BusLosTrapEnable OBJECT-TYPE
			SYNTAX AlarmEnable
			MAX-ACCESS read-write
			STATUS current
			DESCRIPTION
				"10 MHz signal not detected in bus Trap Enable"
		::= { sem2000c01v1Entry 32 }

		-- 1.3.6.1.4.1.10106.3.101291.1.1.33
		sem2000c01v1SerialNo OBJECT-TYPE
			SYNTAX SerialNo
			MAX-ACCESS read-only
			STATUS current
			DESCRIPTION
				"Serial number"
		::= { sem2000c01v1Entry 33 }

		-- 1.3.6.1.4.1.10106.3.587301
		gps3003c02v1 OBJECT IDENTIFIER ::= { albalaProducts 587301 }

		-- 1.3.6.1.4.1.10106.3.587301.1
		gps3003c02v1Table  OBJECT-TYPE
			SYNTAX SEQUENCE OF Gps3003c02v1Entry
			MAX-ACCESS not-accessible
			STATUS current
			DESCRIPTION
				"Module  GPS3003C02V1 Table"
			::= { gps3003c02v1 1 }

		-- 1.3.6.1.4.1.10106.3.587301.1.1
		gps3003c02v1Entry  OBJECT-TYPE
			SYNTAX Gps3003c02v1Entry
			MAX-ACCESS not-accessible
			STATUS current
			DESCRIPTION
				"Module GPS3003C02V1 Entry"
			INDEX { gps3003c02v1Index }
			::= { gps3003c02v1Table 1 }

			Gps3003c02v1Entry ::=
			SEQUENCE {
				gps3003c02v1Index
				ModuleIndex,
				gps3003c02v1SyncMode
				Gps2SyncMode,
				gps3003c02v1PtpSrvEnable
				Bit0No1Yes,
				gps3003c02v1PtpCliEnable
				Bit0No1Yes,
				gps3003c02v1InfoTimePps
				Bit0No1Yes,
				gps3003c02v1PtpDelayAsym
				TimeX1Ns,
				gps3003c02v1HoldoverTout
				GpsHoldovrTime,
				gps3003c02v1CableDelay
				DelayX1Ns,
				gps3003c02v1FTimeDriftEst
				Gps2FrqTimDrf,
				gps3003c02v1FTempDriftEst
				Gps2FrqTemDrf,
				gps3003c02v1Longitude
				AngleDeg1,
				gps3003c02v1Latitude
				AngleDeg1,
				gps3003c02v1Altitude
				AltitudeM1,
				gps3003c02v1IpAdd0
				Uint8,
				gps3003c02v1IpAdd1
				Uint8,
				gps3003c02v1IpAdd2
				Uint8,
				gps3003c02v1IpAdd3
				Uint8,
				gps3003c02v1IpMask0
				Uint8,
				gps3003c02v1IpMask1
				Uint8,
				gps3003c02v1IpMask2
				Uint8,
				gps3003c02v1IpMask3
				Uint8,
				gps3003c02v1IpGway0
				Uint8,
				gps3003c02v1IpGway1
				Uint8,
				gps3003c02v1IpGway2
				Uint8,
				gps3003c02v1IpGway3
				Uint8,
				gps3003c02v1Profile
				PtpProfile,
				gps3003c02v1DelayMechanism
				PtpDelayMech,
				gps3003c02v1Priority1
				Uint8,
				gps3003c02v1Priority2
				Uint8,
				gps3003c02v1DomainNumber
				Uint8,
				gps3003c02v1LogAnnounceInt
				PtpInterval,
				gps3003c02v1LogSyncInt
				PtpInterval,
				gps3003c02v1LogMinDRInt
				PtpInterval,
				gps3003c02v1LogMinPdRInt
				PtpInterval,
				gps3003c02v1AnnounceRTout
				Uint4,
				gps3003c02v1ClockClass
				Uint8,
				gps3003c02v1PtpState
				PtpState,
				gps3003c02v1GnssLos
				BitFail,
				gps3003c02v1GnssLosTrapEnable
				AlarmEnable,
				gps3003c02v1GnssPpsLos
				BitFail,
				gps3003c02v1GnssPpsLosTrapEnable
				AlarmEnable,
				gps3003c02v1GnssUnlock
				BitFail,
				gps3003c02v1GnssUnlockTrapEnable
				AlarmEnable,
				gps3003c02v1GnssPpsErr
				BitFail,
				gps3003c02v1GnssPpsErrTrapEnable
				AlarmEnable,
				gps3003c02v1PtpLos
				BitFail,
				gps3003c02v1PtpLosTrapEnable
				AlarmEnable,
				gps3003c02v1PtpPpsLos
				BitFail,
				gps3003c02v1PtpPpsLosTrapEnable
				AlarmEnable,
				gps3003c02v1PtpUnlock
				BitFail,
				gps3003c02v1PtpUnlockTrapEnable
				AlarmEnable,
				gps3003c02v1PtpPpsErr
				BitFail,
				gps3003c02v1PtpPpsErrTrapEnable
				AlarmEnable,
				gps3003c02v1SyncState
				Gps2SyncState,
				gps3003c02v1SyncStateTrapEnable
				AlarmEnable,
				gps3003c02v1ValidPps
				Bit0No1Yes,
				gps3003c02v1ValidPpsTrapEnable
				AlarmEnable,
				gps3003c02v1ModuleActive
				Bit0No1Yes,
				gps3003c02v1ModuleActiveTrapEnable
				AlarmEnable,
				gps3003c02v1RedSyncState
				Gps2SyncState,
				gps3003c02v1RedSyncStateTrapEnable
				AlarmEnable,
				gps3003c02v1RedModule
				Bit0No1Yes,
				gps3003c02v1RedModuleTrapEnable
				AlarmEnable,
				gps3003c02v1FixMode
				Gps2FixMode,
				gps3003c02v1FixModeTrapEnable
				AlarmEnable,
				gps3003c02v1DiffMode
				Bit0No1Yes,
				gps3003c02v1NumUsedSats
				Uint8,
				gps3003c02v1CN0Max
				LevelDbHz,
				gps3003c02v1PositionAcc
				AltitudeM1,
				gps3003c02v1TimTosOffset
				TimeX1Ns,
				gps3003c02v1SurveyTout
				TimeS2,
				gps3003c02v1HoldoverTime
				GpsHoldovrTime,
				gps3003c02v1PowerStat
				Bit0Ok1Fail,
				gps3003c02v1PowerStatTrapEnable
				AlarmEnable,
				gps3003c02v1AntennaStat
				GpsAntenaStat,
				gps3003c02v1AntennaStatTrapEnable
				AlarmEnable,
				gps3003c02v1EthLink
				Bit0No1Yes,
				gps3003c02v1EthLinkTrapEnable
				AlarmEnable,
				gps3003c02v1AdjustingFreq
				Bit0No1Yes,
				gps3003c02v1OcxoWarInProg
				Bit0No1Yes,
				gps3003c02v1OnePpsStat
				Bit0Ina1Act,
				gps3003c02v1OnePpsStatTrapEnable
				AlarmEnable,
				gps3003c02v1OnePps
				BitPps,
				gps3003c02v1GnssDelay
				TimeX1p25Ns,
				gps3003c02v1PtpDelay
				TimeX1p25Ns,
				gps3003c02v1SerialNo
				SerialNo,
				gps3003c02v1GnssModVer
				UbloxF9tVer,
				gps3003c02v1IpNtpSrv0
				Uint8,
				gps3003c02v1IpNtpSrv1
				Uint8,
				gps3003c02v1IpNtpSrv2
				Uint8,
				gps3003c02v1IpNtpSrv3
				Uint8,
				gps3003c02v1TimeDateOk
				BitFailN
			 }

		-- 1.3.6.1.4.1.10106.3.101291.1.1.1
		gps3003c02v1Index OBJECT-TYPE
			SYNTAX ModuleIndex
			MAX-ACCESS read-only
			STATUS current
			DESCRIPTION
				"Index of GPS3003C02V1 Table"
		::= { gps3003c02v1Entry 1 }

		-- 1.3.6.1.4.1.10106.3.101291.1.1.3
		gps3003c02v1SyncMode OBJECT-TYPE
			SYNTAX Gps2SyncMode
			MAX-ACCESS read-write
			STATUS current
			DESCRIPTION
				"Allows selecting the synchronization mode"
		::= { gps3003c02v1Entry 3 }

		-- 1.3.6.1.4.1.10106.3.101291.1.1.5
		gps3003c02v1PtpSrvEnable OBJECT-TYPE
			SYNTAX Bit0No1Yes
			MAX-ACCESS read-write
			STATUS current
			DESCRIPTION
				"Allows enabling the PTP server when Sync mode is GNSS"
		::= { gps3003c02v1Entry 5 }

		-- 1.3.6.1.4.1.10106.3.101291.1.1.7
		gps3003c02v1PtpCliEnable OBJECT-TYPE
			SYNTAX Bit0No1Yes
			MAX-ACCESS read-write
			STATUS current
			DESCRIPTION
				"Allows enabling the PTP client for logging when Sync mode is GNSS"
		::= { gps3003c02v1Entry 7 }

		-- 1.3.6.1.4.1.10106.3.101291.1.1.9
		gps3003c02v1InfoTimePps OBJECT-TYPE
			SYNTAX Bit0No1Yes
			MAX-ACCESS read-write
			STATUS current
			DESCRIPTION
				"Allows embedding PTP timestamp in 1 PPS signal"
		::= { gps3003c02v1Entry 9 }

		-- 1.3.6.1.4.1.10106.3.101291.1.1.11
		gps3003c02v1PtpDelayAsym OBJECT-TYPE
			SYNTAX TimeX1Ns
			MAX-ACCESS read-write
			STATUS current
			DESCRIPTION
				"Allows compensating the PTP delay asymmetry"
		::= { gps3003c02v1Entry 11 }

		-- 1.3.6.1.4.1.10106.3.101291.1.1.13
		gps3003c02v1HoldoverTout OBJECT-TYPE
			SYNTAX GpsHoldovrTime
			MAX-ACCESS read-write
			STATUS current
			DESCRIPTION
				"Allows selecting the maximum holdover time"
		::= { gps3003c02v1Entry 13 }

		-- 1.3.6.1.4.1.10106.3.101291.1.1.15
		gps3003c02v1CableDelay OBJECT-TYPE
			SYNTAX DelayX1Ns
			MAX-ACCESS read-write
			STATUS current
			DESCRIPTION
				"Allows compensating the antenna cable delay"
		::= { gps3003c02v1Entry 15 }

		-- 1.3.6.1.4.1.10106.3.101291.1.1.17
		gps3003c02v1FTimeDriftEst OBJECT-TYPE
			SYNTAX Gps2FrqTimDrf
			MAX-ACCESS read-only
			STATUS current
			DESCRIPTION
				"Frequency time drift estimation"
		::= { gps3003c02v1Entry 17 }

		-- 1.3.6.1.4.1.10106.3.101291.1.1.19
		gps3003c02v1FTempDriftEst OBJECT-TYPE
			SYNTAX Gps2FrqTemDrf
			MAX-ACCESS read-only
			STATUS current
			DESCRIPTION
				"Frequency temperature drift estimation"
		::= { gps3003c02v1Entry 19 }

		-- 1.3.6.1.4.1.10106.3.101291.1.1.21
		gps3003c02v1Longitude OBJECT-TYPE
			SYNTAX AngleDeg1
			MAX-ACCESS read-only
			STATUS current
			DESCRIPTION
				"GNSS receiver reported longitude"
		::= { gps3003c02v1Entry 21 }

		-- 1.3.6.1.4.1.10106.3.101291.1.1.23
		gps3003c02v1Latitude OBJECT-TYPE
			SYNTAX AngleDeg1
			MAX-ACCESS read-only
			STATUS current
			DESCRIPTION
				"GNSS receiver reported latitude"
		::= { gps3003c02v1Entry 23 }

		-- 1.3.6.1.4.1.10106.3.101291.1.1.25
		gps3003c02v1Altitude OBJECT-TYPE
			SYNTAX AltitudeM1
			MAX-ACCESS read-only
			STATUS current
			DESCRIPTION
				"GNSS receiver reported altitude"
		::= { gps3003c02v1Entry 25 }

		-- 1.3.6.1.4.1.10106.3.101291.1.1.27
		gps3003c02v1IpAdd0 OBJECT-TYPE
			SYNTAX Uint8
			MAX-ACCESS read-write
			STATUS current
			DESCRIPTION
				"Unicast IP address (0)"
		::= { gps3003c02v1Entry 27 }

		-- 1.3.6.1.4.1.10106.3.101291.1.1.29
		gps3003c02v1IpAdd1 OBJECT-TYPE
			SYNTAX Uint8
			MAX-ACCESS read-write
			STATUS current
			DESCRIPTION
				"Unicast IP address (1)"
		::= { gps3003c02v1Entry 29 }

		-- 1.3.6.1.4.1.10106.3.101291.1.1.31
		gps3003c02v1IpAdd2 OBJECT-TYPE
			SYNTAX Uint8
			MAX-ACCESS read-write
			STATUS current
			DESCRIPTION
				"Unicast IP address (2)"
		::= { gps3003c02v1Entry 31 }

		-- 1.3.6.1.4.1.10106.3.101291.1.1.33
		gps3003c02v1IpAdd3 OBJECT-TYPE
			SYNTAX Uint8
			MAX-ACCESS read-write
			STATUS current
			DESCRIPTION
				"Unicast IP address (3)"
		::= { gps3003c02v1Entry 33 }

		-- 1.3.6.1.4.1.10106.3.101291.1.1.35
		gps3003c02v1IpMask0 OBJECT-TYPE
			SYNTAX Uint8
			MAX-ACCESS read-write
			STATUS current
			DESCRIPTION
				"IP mask (0)"
		::= { gps3003c02v1Entry 35 }

		-- 1.3.6.1.4.1.10106.3.101291.1.1.37
		gps3003c02v1IpMask1 OBJECT-TYPE
			SYNTAX Uint8
			MAX-ACCESS read-write
			STATUS current
			DESCRIPTION
				"IP mask (1)"
		::= { gps3003c02v1Entry 37 }

		-- 1.3.6.1.4.1.10106.3.101291.1.1.39
		gps3003c02v1IpMask2 OBJECT-TYPE
			SYNTAX Uint8
			MAX-ACCESS read-write
			STATUS current
			DESCRIPTION
				"IP mask (2)"
		::= { gps3003c02v1Entry 39 }

		-- 1.3.6.1.4.1.10106.3.101291.1.1.41
		gps3003c02v1IpMask3 OBJECT-TYPE
			SYNTAX Uint8
			MAX-ACCESS read-write
			STATUS current
			DESCRIPTION
				"IP mask (3)"
		::= { gps3003c02v1Entry 41 }

		-- 1.3.6.1.4.1.10106.3.101291.1.1.43
		gps3003c02v1IpGway0 OBJECT-TYPE
			SYNTAX Uint8
			MAX-ACCESS read-write
			STATUS current
			DESCRIPTION
				"Gateway IP address (0)"
		::= { gps3003c02v1Entry 43 }

		-- 1.3.6.1.4.1.10106.3.101291.1.1.45
		gps3003c02v1IpGway1 OBJECT-TYPE
			SYNTAX Uint8
			MAX-ACCESS read-write
			STATUS current
			DESCRIPTION
				"Gateway IP address (1)"
		::= { gps3003c02v1Entry 45 }

		-- 1.3.6.1.4.1.10106.3.101291.1.1.47
		gps3003c02v1IpGway2 OBJECT-TYPE
			SYNTAX Uint8
			MAX-ACCESS read-write
			STATUS current
			DESCRIPTION
				"Gateway IP address (2)"
		::= { gps3003c02v1Entry 47 }

		-- 1.3.6.1.4.1.10106.3.101291.1.1.49
		gps3003c02v1IpGway3 OBJECT-TYPE
			SYNTAX Uint8
			MAX-ACCESS read-write
			STATUS current
			DESCRIPTION
				"Gateway IP address (3)"
		::= { gps3003c02v1Entry 49 }

		-- 1.3.6.1.4.1.10106.3.101291.1.1.51
		gps3003c02v1Profile OBJECT-TYPE
			SYNTAX PtpProfile
			MAX-ACCESS read-write
			STATUS current
			DESCRIPTION
				"Allows loading default values of a PTP profile"
		::= { gps3003c02v1Entry 51 }

		-- 1.3.6.1.4.1.10106.3.101291.1.1.53
		gps3003c02v1DelayMechanism OBJECT-TYPE
			SYNTAX PtpDelayMech
			MAX-ACCESS read-write
			STATUS current
			DESCRIPTION
				"Allows selecting the delay mechanism"
		::= { gps3003c02v1Entry 53 }

		-- 1.3.6.1.4.1.10106.3.101291.1.1.55
		gps3003c02v1Priority1 OBJECT-TYPE
			SYNTAX Uint8
			MAX-ACCESS read-write
			STATUS current
			DESCRIPTION
				"Allows selecting the Priority1 attribute of the local clock. It is used in the best master selection algorithm"
		::= { gps3003c02v1Entry 55 }

		-- 1.3.6.1.4.1.10106.3.101291.1.1.57
		gps3003c02v1Priority2 OBJECT-TYPE
			SYNTAX Uint8
			MAX-ACCESS read-write
			STATUS current
			DESCRIPTION
				"Allows selecting the Priority2 attribute of the local clock. It is used in the best master selection algorithm"
		::= { gps3003c02v1Entry 57 }

		-- 1.3.6.1.4.1.10106.3.101291.1.1.59
		gps3003c02v1DomainNumber OBJECT-TYPE
			SYNTAX Uint8
			MAX-ACCESS read-write
			STATUS current
			DESCRIPTION
				"Allows selecting the Domanin number attribute of the local clock"
		::= { gps3003c02v1Entry 59 }

		-- 1.3.6.1.4.1.10106.3.101291.1.1.61
		gps3003c02v1LogAnnounceInt OBJECT-TYPE
			SYNTAX PtpInterval
			MAX-ACCESS read-write
			STATUS current
			DESCRIPTION
				"Allows selecting the mean interval between Announce messages"
		::= { gps3003c02v1Entry 61 }

		-- 1.3.6.1.4.1.10106.3.101291.1.1.63
		gps3003c02v1LogSyncInt OBJECT-TYPE
			SYNTAX PtpInterval
			MAX-ACCESS read-write
			STATUS current
			DESCRIPTION
				"Allows selecting the mean interval between Sync messages"
		::= { gps3003c02v1Entry 63 }

		-- 1.3.6.1.4.1.10106.3.101291.1.1.65
		gps3003c02v1LogMinDRInt OBJECT-TYPE
			SYNTAX PtpInterval
			MAX-ACCESS read-write
			STATUS current
			DESCRIPTION
				"Allows selecting the minimum mean interval between Delay_Req messages"
		::= { gps3003c02v1Entry 65 }

		-- 1.3.6.1.4.1.10106.3.101291.1.1.67
		gps3003c02v1LogMinPdRInt OBJECT-TYPE
			SYNTAX PtpInterval
			MAX-ACCESS read-write
			STATUS current
			DESCRIPTION
				"Allows selecting the minimum mean interval between Pdelay_Req messages"
		::= { gps3003c02v1Entry 67 }

		-- 1.3.6.1.4.1.10106.3.101291.1.1.69
		gps3003c02v1AnnounceRTout OBJECT-TYPE
			SYNTAX Uint4
			MAX-ACCESS read-write
			STATUS current
			DESCRIPTION
				"Allows selecting the number of missed Announce messages before the last Announce messages expires"
		::= { gps3003c02v1Entry 69 }

		-- 1.3.6.1.4.1.10106.3.101291.1.1.71
		gps3003c02v1ClockClass OBJECT-TYPE
			SYNTAX Uint8
			MAX-ACCESS read-only
			STATUS current
			DESCRIPTION
				"Indicates the value of the ClockClass attribute of the local clock"
		::= { gps3003c02v1Entry 71 }

		-- 1.3.6.1.4.1.10106.3.101291.1.1.73
		gps3003c02v1PtpState OBJECT-TYPE
			SYNTAX PtpState
			MAX-ACCESS read-only
			STATUS current
			DESCRIPTION
				"Indicates the PTP state"
		::= { gps3003c02v1Entry 73 }

		-- 1.3.6.1.4.1.10106.3.101291.1.1.75
		gps3003c02v1GnssLos OBJECT-TYPE
			SYNTAX BitFail
			MAX-ACCESS read-only
			STATUS current
			DESCRIPTION
				"GNSS loss of signal. To be cleared it has to be for 30 s in in 3D-FIX or Time mode"
		::= { gps3003c02v1Entry 75 }

		-- 1.3.6.1.4.1.10106.3.101291.1.1.76
		gps3003c02v1GnssLosTrapEnable OBJECT-TYPE
			SYNTAX AlarmEnable
			MAX-ACCESS read-write
			STATUS current
			DESCRIPTION
				"GNSS loss of signal. To be cleared it has to be for 30 s in in 3D-FIX or Time mode Trap Enable"
		::= { gps3003c02v1Entry 76 }

		-- 1.3.6.1.4.1.10106.3.101291.1.1.77
		gps3003c02v1GnssPpsLos OBJECT-TYPE
			SYNTAX BitFail
			MAX-ACCESS read-only
			STATUS current
			DESCRIPTION
				"GNSS loss of PPS. It is cleared when the error of the PPS delivered by GNSS module is less than 5 ns. It is set when the delay is greater than 50 ns"
		::= { gps3003c02v1Entry 77 }

		-- 1.3.6.1.4.1.10106.3.101291.1.1.78
		gps3003c02v1GnssPpsLosTrapEnable OBJECT-TYPE
			SYNTAX AlarmEnable
			MAX-ACCESS read-write
			STATUS current
			DESCRIPTION
				"GNSS loss of PPS. It is cleared when the error of the PPS delivered by GNSS module is less than 5 ns. It is set when the delay is greater than 50 ns Trap Enable"
		::= { gps3003c02v1Entry 78 }

		-- 1.3.6.1.4.1.10106.3.101291.1.1.79
		gps3003c02v1GnssUnlock OBJECT-TYPE
			SYNTAX BitFail
			MAX-ACCESS read-only
			STATUS current
			DESCRIPTION
				"GNSS PPS unlock. It is cleared when the error of the output PPS is less than 10 ns. It is set when the error is greater than 100 ns."
		::= { gps3003c02v1Entry 79 }

		-- 1.3.6.1.4.1.10106.3.101291.1.1.80
		gps3003c02v1GnssUnlockTrapEnable OBJECT-TYPE
			SYNTAX AlarmEnable
			MAX-ACCESS read-write
			STATUS current
			DESCRIPTION
				"GNSS PPS unlock. It is cleared when the error of the output PPS is less than 10 ns. It is set when the error is greater than 100 ns. Trap Enable"
		::= { gps3003c02v1Entry 80 }

		-- 1.3.6.1.4.1.10106.3.101291.1.1.81
		gps3003c02v1GnssPpsErr OBJECT-TYPE
			SYNTAX BitFail
			MAX-ACCESS read-only
			STATUS current
			DESCRIPTION
				"GNSS pulse error. It is cleared when the error of the output PPS is less than the value specified in 'GNSS valid PPS margin'. It is set when the error is greater than this value."
		::= { gps3003c02v1Entry 81 }

		-- 1.3.6.1.4.1.10106.3.101291.1.1.82
		gps3003c02v1GnssPpsErrTrapEnable OBJECT-TYPE
			SYNTAX AlarmEnable
			MAX-ACCESS read-write
			STATUS current
			DESCRIPTION
				"GNSS pulse error. It is cleared when the error of the output PPS is less than the value specified in 'GNSS valid PPS margin'. It is set when the error is greater than this value. Trap Enable"
		::= { gps3003c02v1Entry 82 }

		-- 1.3.6.1.4.1.10106.3.101291.1.1.83
		gps3003c02v1PtpLos OBJECT-TYPE
			SYNTAX BitFail
			MAX-ACCESS read-only
			STATUS current
			DESCRIPTION
				"PTP loss of signal.It is cleared when the PTP module is in Slave or Uncalibrated mode"
		::= { gps3003c02v1Entry 83 }

		-- 1.3.6.1.4.1.10106.3.101291.1.1.84
		gps3003c02v1PtpLosTrapEnable OBJECT-TYPE
			SYNTAX AlarmEnable
			MAX-ACCESS read-write
			STATUS current
			DESCRIPTION
				"PTP loss of signal.It is cleared when the PTP module is in Slave or Uncalibrated mode Trap Enable"
		::= { gps3003c02v1Entry 84 }

		-- 1.3.6.1.4.1.10106.3.101291.1.1.85
		gps3003c02v1PtpPpsLos OBJECT-TYPE
			SYNTAX BitFail
			MAX-ACCESS read-only
			STATUS current
			DESCRIPTION
				"PTP loss of PPS. It is cleared after 30 s receiving a valid PPS from PTP module"
		::= { gps3003c02v1Entry 85 }

		-- 1.3.6.1.4.1.10106.3.101291.1.1.86
		gps3003c02v1PtpPpsLosTrapEnable OBJECT-TYPE
			SYNTAX AlarmEnable
			MAX-ACCESS read-write
			STATUS current
			DESCRIPTION
				"PTP loss of PPS. It is cleared after 30 s receiving a valid PPS from PTP module Trap Enable"
		::= { gps3003c02v1Entry 86 }

		-- 1.3.6.1.4.1.10106.3.101291.1.1.87
		gps3003c02v1PtpUnlock OBJECT-TYPE
			SYNTAX BitFail
			MAX-ACCESS read-only
			STATUS current
			DESCRIPTION
				"PTP PPS unlock. It is cleared when the error of the output PPS is less than 25 ns. It is set when the error is greater than 250 ns."
		::= { gps3003c02v1Entry 87 }

		-- 1.3.6.1.4.1.10106.3.101291.1.1.88
		gps3003c02v1PtpUnlockTrapEnable OBJECT-TYPE
			SYNTAX AlarmEnable
			MAX-ACCESS read-write
			STATUS current
			DESCRIPTION
				"PTP PPS unlock. It is cleared when the error of the output PPS is less than 25 ns. It is set when the error is greater than 250 ns. Trap Enable"
		::= { gps3003c02v1Entry 88 }

		-- 1.3.6.1.4.1.10106.3.101291.1.1.89
		gps3003c02v1PtpPpsErr OBJECT-TYPE
			SYNTAX BitFail
			MAX-ACCESS read-only
			STATUS current
			DESCRIPTION
				"PTP PPS error. It is cleared when the error of the output PPS is less than the value specified in 'PTP valid PPS margin'. It is set when the error is greater than this value."
		::= { gps3003c02v1Entry 89 }

		-- 1.3.6.1.4.1.10106.3.101291.1.1.90
		gps3003c02v1PtpPpsErrTrapEnable OBJECT-TYPE
			SYNTAX AlarmEnable
			MAX-ACCESS read-write
			STATUS current
			DESCRIPTION
				"PTP PPS error. It is cleared when the error of the output PPS is less than the value specified in 'PTP valid PPS margin'. It is set when the error is greater than this value. Trap Enable"
		::= { gps3003c02v1Entry 90 }

		-- 1.3.6.1.4.1.10106.3.101291.1.1.91
		gps3003c02v1SyncState OBJECT-TYPE
			SYNTAX Gps2SyncState
			MAX-ACCESS read-only
			STATUS current
			DESCRIPTION
				"Indicates the synchronization state"
		::= { gps3003c02v1Entry 91 }

		-- 1.3.6.1.4.1.10106.3.101291.1.1.92
		gps3003c02v1SyncStateTrapEnable OBJECT-TYPE
			SYNTAX AlarmEnable
			MAX-ACCESS read-write
			STATUS current
			DESCRIPTION
				"Indicates the synchronization state Trap Enable"
		::= { gps3003c02v1Entry 92 }

		-- 1.3.6.1.4.1.10106.3.101291.1.1.93
		gps3003c02v1ValidPps OBJECT-TYPE
			SYNTAX Bit0No1Yes
			MAX-ACCESS read-only
			STATUS current
			DESCRIPTION
				"Indicates that the internally generated PPS signal has been phase aligned with an external reference (GNSS or PTP)"
		::= { gps3003c02v1Entry 93 }

		-- 1.3.6.1.4.1.10106.3.101291.1.1.94
		gps3003c02v1ValidPpsTrapEnable OBJECT-TYPE
			SYNTAX AlarmEnable
			MAX-ACCESS read-write
			STATUS current
			DESCRIPTION
				"Indicates that the internally generated PPS signal has been phase aligned with an external reference (GNSS or PTP) Trap Enable"
		::= { gps3003c02v1Entry 94 }

		-- 1.3.6.1.4.1.10106.3.101291.1.1.95
		gps3003c02v1ModuleActive OBJECT-TYPE
			SYNTAX Bit0No1Yes
			MAX-ACCESS read-only
			STATUS current
			DESCRIPTION
				"Indicates that this module is the one that provides the reference signals"
		::= { gps3003c02v1Entry 95 }

		-- 1.3.6.1.4.1.10106.3.101291.1.1.96
		gps3003c02v1ModuleActiveTrapEnable OBJECT-TYPE
			SYNTAX AlarmEnable
			MAX-ACCESS read-write
			STATUS current
			DESCRIPTION
				"Indicates that this module is the one that provides the reference signals Trap Enable"
		::= { gps3003c02v1Entry 96 }

		-- 1.3.6.1.4.1.10106.3.101291.1.1.97
		gps3003c02v1RedSyncState OBJECT-TYPE
			SYNTAX Gps2SyncState
			MAX-ACCESS read-only
			STATUS current
			DESCRIPTION
				"Indicates the redundant module's synchronization state"
		::= { gps3003c02v1Entry 97 }

		-- 1.3.6.1.4.1.10106.3.101291.1.1.98
		gps3003c02v1RedSyncStateTrapEnable OBJECT-TYPE
			SYNTAX AlarmEnable
			MAX-ACCESS read-write
			STATUS current
			DESCRIPTION
				"Indicates the redundant module's synchronization state Trap Enable"
		::= { gps3003c02v1Entry 98 }

		-- 1.3.6.1.4.1.10106.3.101291.1.1.99
		gps3003c02v1RedModule OBJECT-TYPE
			SYNTAX Bit0No1Yes
			MAX-ACCESS read-only
			STATUS current
			DESCRIPTION
				"Indicates if the redundant module is present"
		::= { gps3003c02v1Entry 99 }

		-- 1.3.6.1.4.1.10106.3.101291.1.1.100
		gps3003c02v1RedModuleTrapEnable OBJECT-TYPE
			SYNTAX AlarmEnable
			MAX-ACCESS read-write
			STATUS current
			DESCRIPTION
				"Indicates if the redundant module is present Trap Enable"
		::= { gps3003c02v1Entry 100 }

		-- 1.3.6.1.4.1.10106.3.101291.1.1.101
		gps3003c02v1FixMode OBJECT-TYPE
			SYNTAX Gps2FixMode
			MAX-ACCESS read-only
			STATUS current
			DESCRIPTION
				"GNSS receiver module satellite tracking mode"
		::= { gps3003c02v1Entry 101 }

		-- 1.3.6.1.4.1.10106.3.101291.1.1.102
		gps3003c02v1FixModeTrapEnable OBJECT-TYPE
			SYNTAX AlarmEnable
			MAX-ACCESS read-write
			STATUS current
			DESCRIPTION
				"GNSS receiver module satellite tracking mode Trap Enable"
		::= { gps3003c02v1Entry 102 }

		-- 1.3.6.1.4.1.10106.3.101291.1.1.103
		gps3003c02v1DiffMode OBJECT-TYPE
			SYNTAX Bit0No1Yes
			MAX-ACCESS read-only
			STATUS current
			DESCRIPTION
				"GNSS receiver receives correction data and uses them to improve provided solution"
		::= { gps3003c02v1Entry 103 }

		-- 1.3.6.1.4.1.10106.3.101291.1.1.105
		gps3003c02v1NumUsedSats OBJECT-TYPE
			SYNTAX Uint8
			MAX-ACCESS read-only
			STATUS current
			DESCRIPTION
				"Number of GNSS used in current fix"
		::= { gps3003c02v1Entry 105 }

		-- 1.3.6.1.4.1.10106.3.101291.1.1.107
		gps3003c02v1CN0Max OBJECT-TYPE
			SYNTAX LevelDbHz
			MAX-ACCESS read-only
			STATUS current
			DESCRIPTION
				"Estimated carrier to noise ratio for the best satellite in tracking"
		::= { gps3003c02v1Entry 107 }

		-- 1.3.6.1.4.1.10106.3.101291.1.1.109
		gps3003c02v1PositionAcc OBJECT-TYPE
			SYNTAX AltitudeM1
			MAX-ACCESS read-only
			STATUS current
			DESCRIPTION
				"Estimated position accuracy"
		::= { gps3003c02v1Entry 109 }

		-- 1.3.6.1.4.1.10106.3.101291.1.1.111
		gps3003c02v1TimTosOffset OBJECT-TYPE
			SYNTAX TimeX1Ns
			MAX-ACCESS read-only
			STATUS current
			DESCRIPTION
				"Estimated GNSS module PPS error"
		::= { gps3003c02v1Entry 111 }

		-- 1.3.6.1.4.1.10106.3.101291.1.1.113
		gps3003c02v1SurveyTout OBJECT-TYPE
			SYNTAX TimeS2
			MAX-ACCESS read-only
			STATUS current
			DESCRIPTION
				"Time to exit Survey-in"
		::= { gps3003c02v1Entry 113 }

		-- 1.3.6.1.4.1.10106.3.101291.1.1.115
		gps3003c02v1HoldoverTime OBJECT-TYPE
			SYNTAX GpsHoldovrTime
			MAX-ACCESS read-only
			STATUS current
			DESCRIPTION
				"Holdover time"
		::= { gps3003c02v1Entry 115 }

		-- 1.3.6.1.4.1.10106.3.101291.1.1.117
		gps3003c02v1PowerStat OBJECT-TYPE
			SYNTAX Bit0Ok1Fail
			MAX-ACCESS read-only
			STATUS current
			DESCRIPTION
				"Indicates the power supply status"
		::= { gps3003c02v1Entry 117 }

		-- 1.3.6.1.4.1.10106.3.101291.1.1.118
		gps3003c02v1PowerStatTrapEnable OBJECT-TYPE
			SYNTAX AlarmEnable
			MAX-ACCESS read-write
			STATUS current
			DESCRIPTION
				"Indicates the power supply status Trap Enable"
		::= { gps3003c02v1Entry 118 }

		-- 1.3.6.1.4.1.10106.3.101291.1.1.119
		gps3003c02v1AntennaStat OBJECT-TYPE
			SYNTAX GpsAntenaStat
			MAX-ACCESS read-only
			STATUS current
			DESCRIPTION
				"Indicates the antenna connection status"
		::= { gps3003c02v1Entry 119 }

		-- 1.3.6.1.4.1.10106.3.101291.1.1.120
		gps3003c02v1AntennaStatTrapEnable OBJECT-TYPE
			SYNTAX AlarmEnable
			MAX-ACCESS read-write
			STATUS current
			DESCRIPTION
				"Indicates the antenna connection status Trap Enable"
		::= { gps3003c02v1Entry 120 }

		-- 1.3.6.1.4.1.10106.3.101291.1.1.121
		gps3003c02v1EthLink OBJECT-TYPE
			SYNTAX Bit0No1Yes
			MAX-ACCESS read-only
			STATUS current
			DESCRIPTION
				"Indicates that the Ethernet link is OK"
		::= { gps3003c02v1Entry 121 }

		-- 1.3.6.1.4.1.10106.3.101291.1.1.122
		gps3003c02v1EthLinkTrapEnable OBJECT-TYPE
			SYNTAX AlarmEnable
			MAX-ACCESS read-write
			STATUS current
			DESCRIPTION
				"Indicates that the Ethernet link is OK Trap Enable"
		::= { gps3003c02v1Entry 122 }

		-- 1.3.6.1.4.1.10106.3.101291.1.1.123
		gps3003c02v1AdjustingFreq OBJECT-TYPE
			SYNTAX Bit0No1Yes
			MAX-ACCESS read-only
			STATUS current
			DESCRIPTION
				"Indicates that the module is adjusting the frequency"
		::= { gps3003c02v1Entry 123 }

		-- 1.3.6.1.4.1.10106.3.101291.1.1.125
		gps3003c02v1OcxoWarInProg OBJECT-TYPE
			SYNTAX Bit0No1Yes
			MAX-ACCESS read-only
			STATUS current
			DESCRIPTION
				"Indicates that the OCXO warming is in progress"
		::= { gps3003c02v1Entry 125 }

		-- 1.3.6.1.4.1.10106.3.101291.1.1.127
		gps3003c02v1OnePpsStat OBJECT-TYPE
			SYNTAX Bit0Ina1Act
			MAX-ACCESS read-only
			STATUS current
			DESCRIPTION
				"Indicates that the module is delivering a valid PPS"
		::= { gps3003c02v1Entry 127 }

		-- 1.3.6.1.4.1.10106.3.101291.1.1.128
		gps3003c02v1OnePpsStatTrapEnable OBJECT-TYPE
			SYNTAX AlarmEnable
			MAX-ACCESS read-write
			STATUS current
			DESCRIPTION
				"Indicates that the module is delivering a valid PPS Trap Enable"
		::= { gps3003c02v1Entry 128 }

		-- 1.3.6.1.4.1.10106.3.101291.1.1.129
		gps3003c02v1OnePps OBJECT-TYPE
			SYNTAX BitPps
			MAX-ACCESS read-only
			STATUS current
			DESCRIPTION
				"One pulse per second signal"
		::= { gps3003c02v1Entry 129 }

		-- 1.3.6.1.4.1.10106.3.101291.1.1.131
		gps3003c02v1GnssDelay OBJECT-TYPE
			SYNTAX TimeX1p25Ns
			MAX-ACCESS read-only
			STATUS current
			DESCRIPTION
				"PPS delay relative to GNSS"
		::= { gps3003c02v1Entry 131 }

		-- 1.3.6.1.4.1.10106.3.101291.1.1.133
		gps3003c02v1PtpDelay OBJECT-TYPE
			SYNTAX TimeX1p25Ns
			MAX-ACCESS read-only
			STATUS current
			DESCRIPTION
				"PPS delay relative to PTP"
		::= { gps3003c02v1Entry 133 }

		-- 1.3.6.1.4.1.10106.3.101291.1.1.135
		gps3003c02v1SerialNo OBJECT-TYPE
			SYNTAX SerialNo
			MAX-ACCESS read-only
			STATUS current
			DESCRIPTION
				"Serial number"
		::= { gps3003c02v1Entry 135 }

		-- 1.3.6.1.4.1.10106.3.101291.1.1.137
		gps3003c02v1GnssModVer OBJECT-TYPE
			SYNTAX UbloxF9tVer
			MAX-ACCESS read-only
			STATUS current
			DESCRIPTION
				"GNSS module version"
		::= { gps3003c02v1Entry 137 }

		-- 1.3.6.1.4.1.10106.3.101291.1.1.139
		gps3003c02v1IpNtpSrv0 OBJECT-TYPE
			SYNTAX Uint8
			MAX-ACCESS read-write
			STATUS current
			DESCRIPTION
				"NTP server IP address (0)"
		::= { gps3003c02v1Entry 139 }

		-- 1.3.6.1.4.1.10106.3.101291.1.1.141
		gps3003c02v1IpNtpSrv1 OBJECT-TYPE
			SYNTAX Uint8
			MAX-ACCESS read-write
			STATUS current
			DESCRIPTION
				"NTP server IP address (1)"
		::= { gps3003c02v1Entry 141 }

		-- 1.3.6.1.4.1.10106.3.101291.1.1.143
		gps3003c02v1IpNtpSrv2 OBJECT-TYPE
			SYNTAX Uint8
			MAX-ACCESS read-write
			STATUS current
			DESCRIPTION
				"NTP server IP address (2)"
		::= { gps3003c02v1Entry 143 }

		-- 1.3.6.1.4.1.10106.3.101291.1.1.145
		gps3003c02v1IpNtpSrv3 OBJECT-TYPE
			SYNTAX Uint8
			MAX-ACCESS read-write
			STATUS current
			DESCRIPTION
				"NTP server IP address (3)"
		::= { gps3003c02v1Entry 145 }

		-- 1.3.6.1.4.1.10106.3.101291.1.1.147
		gps3003c02v1TimeDateOk OBJECT-TYPE
			SYNTAX BitFailN
			MAX-ACCESS read-only
			STATUS current
			DESCRIPTION
				"Time and date OK"
		::= { gps3003c02v1Entry 147 }

		-- 1.3.6.1.4.1.10106.3.587501
		gps3003c03v1 OBJECT IDENTIFIER ::= { albalaProducts 587501 }

		-- 1.3.6.1.4.1.10106.3.587501.1
		gps3003c03v1Table  OBJECT-TYPE
			SYNTAX SEQUENCE OF Gps3003c03v1Entry
			MAX-ACCESS not-accessible
			STATUS current
			DESCRIPTION
				"Module  GPS3003C03V1 Table"
			::= { gps3003c03v1 1 }

		-- 1.3.6.1.4.1.10106.3.587501.1.1
		gps3003c03v1Entry  OBJECT-TYPE
			SYNTAX Gps3003c03v1Entry
			MAX-ACCESS not-accessible
			STATUS current
			DESCRIPTION
				"Module GPS3003C03V1 Entry"
			INDEX { gps3003c03v1Index }
			::= { gps3003c03v1Table 1 }

			Gps3003c03v1Entry ::=
			SEQUENCE {
				gps3003c03v1Index
				ModuleIndex,
				gps3003c03v1SyncMode
				Gps2SyncMode,
				gps3003c03v1PtpSrvEnable
				Bit0No1Yes,
				gps3003c03v1PtpCliEnable
				Bit0No1Yes,
				gps3003c03v1InfoTimePps
				Bit0No1Yes,
				gps3003c03v1PtpDelayAsym
				TimeX1Ns,
				gps3003c03v1HoldoverTout
				GpsHoldovrTime,
				gps3003c03v1CableDelay
				DelayX1Ns,
				gps3003c03v1FTimeDriftEst
				Gps2FrqTimDrf,
				gps3003c03v1FTempDriftEst
				Gps2FrqTemDrf,
				gps3003c03v1Longitude
				AngleDeg1,
				gps3003c03v1Latitude
				AngleDeg1,
				gps3003c03v1Altitude
				AltitudeM1,
				gps3003c03v1IpAdd0
				Uint8,
				gps3003c03v1IpAdd1
				Uint8,
				gps3003c03v1IpAdd2
				Uint8,
				gps3003c03v1IpAdd3
				Uint8,
				gps3003c03v1IpMask0
				Uint8,
				gps3003c03v1IpMask1
				Uint8,
				gps3003c03v1IpMask2
				Uint8,
				gps3003c03v1IpMask3
				Uint8,
				gps3003c03v1IpGway0
				Uint8,
				gps3003c03v1IpGway1
				Uint8,
				gps3003c03v1IpGway2
				Uint8,
				gps3003c03v1IpGway3
				Uint8,
				gps3003c03v1Profile
				PtpProfile,
				gps3003c03v1DelayMechanism
				PtpDelayMech,
				gps3003c03v1Priority1
				Uint8,
				gps3003c03v1Priority2
				Uint8,
				gps3003c03v1DomainNumber
				Uint8,
				gps3003c03v1LogAnnounceInt
				PtpInterval,
				gps3003c03v1LogSyncInt
				PtpInterval,
				gps3003c03v1LogMinDRInt
				PtpInterval,
				gps3003c03v1LogMinPdRInt
				PtpInterval,
				gps3003c03v1AnnounceRTout
				Uint4,
				gps3003c03v1ClockClass
				Uint8,
				gps3003c03v1PtpState
				PtpState,
				gps3003c03v1GnssLos
				BitFail,
				gps3003c03v1GnssLosTrapEnable
				AlarmEnable,
				gps3003c03v1GnssPpsLos
				BitFail,
				gps3003c03v1GnssPpsLosTrapEnable
				AlarmEnable,
				gps3003c03v1GnssUnlock
				BitFail,
				gps3003c03v1GnssUnlockTrapEnable
				AlarmEnable,
				gps3003c03v1GnssPpsErr
				BitFail,
				gps3003c03v1GnssPpsErrTrapEnable
				AlarmEnable,
				gps3003c03v1PtpLos
				BitFail,
				gps3003c03v1PtpLosTrapEnable
				AlarmEnable,
				gps3003c03v1PtpPpsLos
				BitFail,
				gps3003c03v1PtpPpsLosTrapEnable
				AlarmEnable,
				gps3003c03v1PtpUnlock
				BitFail,
				gps3003c03v1PtpUnlockTrapEnable
				AlarmEnable,
				gps3003c03v1PtpPpsErr
				BitFail,
				gps3003c03v1PtpPpsErrTrapEnable
				AlarmEnable,
				gps3003c03v1SyncState
				Gps2SyncState,
				gps3003c03v1SyncStateTrapEnable
				AlarmEnable,
				gps3003c03v1ValidPps
				Bit0No1Yes,
				gps3003c03v1ValidPpsTrapEnable
				AlarmEnable,
				gps3003c03v1ModuleActive
				Bit0No1Yes,
				gps3003c03v1ModuleActiveTrapEnable
				AlarmEnable,
				gps3003c03v1RedSyncState
				Gps2SyncState,
				gps3003c03v1RedSyncStateTrapEnable
				AlarmEnable,
				gps3003c03v1RedModule
				Bit0No1Yes,
				gps3003c03v1RedModuleTrapEnable
				AlarmEnable,
				gps3003c03v1FixMode
				Gps2FixMode,
				gps3003c03v1FixModeTrapEnable
				AlarmEnable,
				gps3003c03v1DiffMode
				Bit0No1Yes,
				gps3003c03v1NumUsedSats
				Uint8,
				gps3003c03v1CN0Max
				LevelDbHz,
				gps3003c03v1PositionAcc
				AltitudeM1,
				gps3003c03v1TimTosOffset
				TimeX1Ns,
				gps3003c03v1SurveyTout
				TimeS2,
				gps3003c03v1HoldoverTime
				GpsHoldovrTime,
				gps3003c03v1PowerStat
				Bit0Ok1Fail,
				gps3003c03v1PowerStatTrapEnable
				AlarmEnable,
				gps3003c03v1AntennaStat
				GpsAntenaStat,
				gps3003c03v1AntennaStatTrapEnable
				AlarmEnable,
				gps3003c03v1EthLink
				Bit0No1Yes,
				gps3003c03v1EthLinkTrapEnable
				AlarmEnable,
				gps3003c03v1AdjustingFreq
				Bit0No1Yes,
				gps3003c03v1OcxoWarInProg
				Bit0No1Yes,
				gps3003c03v1OnePpsStat
				Bit0Ina1Act,
				gps3003c03v1OnePpsStatTrapEnable
				AlarmEnable,
				gps3003c03v1OnePps
				BitPps,
				gps3003c03v1GnssDelay
				TimeX1p25Ns,
				gps3003c03v1PtpDelay
				TimeX1p25Ns,
				gps3003c03v1SerialNo
				SerialNo,
				gps3003c03v1GnssModVer
				UbloxF9tVer,
				gps3003c03v1IpNtpSrv0
				Uint8,
				gps3003c03v1IpNtpSrv1
				Uint8,
				gps3003c03v1IpNtpSrv2
				Uint8,
				gps3003c03v1IpNtpSrv3
				Uint8,
				gps3003c03v1TimeDateOk
				BitFailN
			 }

		-- 1.3.6.1.4.1.10106.3.101291.1.1.1
		gps3003c03v1Index OBJECT-TYPE
			SYNTAX ModuleIndex
			MAX-ACCESS read-only
			STATUS current
			DESCRIPTION
				"Index of GPS3003C03V1 Table"
		::= { gps3003c03v1Entry 1 }

		-- 1.3.6.1.4.1.10106.3.101291.1.1.3
		gps3003c03v1SyncMode OBJECT-TYPE
			SYNTAX Gps2SyncMode
			MAX-ACCESS read-write
			STATUS current
			DESCRIPTION
				"Allows selecting the synchronization mode"
		::= { gps3003c03v1Entry 3 }

		-- 1.3.6.1.4.1.10106.3.101291.1.1.5
		gps3003c03v1PtpSrvEnable OBJECT-TYPE
			SYNTAX Bit0No1Yes
			MAX-ACCESS read-write
			STATUS current
			DESCRIPTION
				"Allows enabling the PTP server when Sync mode is GNSS"
		::= { gps3003c03v1Entry 5 }

		-- 1.3.6.1.4.1.10106.3.101291.1.1.7
		gps3003c03v1PtpCliEnable OBJECT-TYPE
			SYNTAX Bit0No1Yes
			MAX-ACCESS read-write
			STATUS current
			DESCRIPTION
				"Allows enabling the PTP client for logging when Sync mode is GNSS"
		::= { gps3003c03v1Entry 7 }

		-- 1.3.6.1.4.1.10106.3.101291.1.1.9
		gps3003c03v1InfoTimePps OBJECT-TYPE
			SYNTAX Bit0No1Yes
			MAX-ACCESS read-write
			STATUS current
			DESCRIPTION
				"Allows embedding PTP timestamp in 1 PPS signal"
		::= { gps3003c03v1Entry 9 }

		-- 1.3.6.1.4.1.10106.3.101291.1.1.11
		gps3003c03v1PtpDelayAsym OBJECT-TYPE
			SYNTAX TimeX1Ns
			MAX-ACCESS read-write
			STATUS current
			DESCRIPTION
				"Allows compensating the PTP delay asymmetry"
		::= { gps3003c03v1Entry 11 }

		-- 1.3.6.1.4.1.10106.3.101291.1.1.13
		gps3003c03v1HoldoverTout OBJECT-TYPE
			SYNTAX GpsHoldovrTime
			MAX-ACCESS read-write
			STATUS current
			DESCRIPTION
				"Allows selecting the maximum holdover time"
		::= { gps3003c03v1Entry 13 }

		-- 1.3.6.1.4.1.10106.3.101291.1.1.15
		gps3003c03v1CableDelay OBJECT-TYPE
			SYNTAX DelayX1Ns
			MAX-ACCESS read-write
			STATUS current
			DESCRIPTION
				"Allows compensating the antenna cable delay"
		::= { gps3003c03v1Entry 15 }

		-- 1.3.6.1.4.1.10106.3.101291.1.1.17
		gps3003c03v1FTimeDriftEst OBJECT-TYPE
			SYNTAX Gps2FrqTimDrf
			MAX-ACCESS read-only
			STATUS current
			DESCRIPTION
				"Frequency time drift estimation"
		::= { gps3003c03v1Entry 17 }

		-- 1.3.6.1.4.1.10106.3.101291.1.1.19
		gps3003c03v1FTempDriftEst OBJECT-TYPE
			SYNTAX Gps2FrqTemDrf
			MAX-ACCESS read-only
			STATUS current
			DESCRIPTION
				"Frequency temperature drift estimation"
		::= { gps3003c03v1Entry 19 }

		-- 1.3.6.1.4.1.10106.3.101291.1.1.21
		gps3003c03v1Longitude OBJECT-TYPE
			SYNTAX AngleDeg1
			MAX-ACCESS read-only
			STATUS current
			DESCRIPTION
				"GNSS receiver reported longitude"
		::= { gps3003c03v1Entry 21 }

		-- 1.3.6.1.4.1.10106.3.101291.1.1.23
		gps3003c03v1Latitude OBJECT-TYPE
			SYNTAX AngleDeg1
			MAX-ACCESS read-only
			STATUS current
			DESCRIPTION
				"GNSS receiver reported latitude"
		::= { gps3003c03v1Entry 23 }

		-- 1.3.6.1.4.1.10106.3.101291.1.1.25
		gps3003c03v1Altitude OBJECT-TYPE
			SYNTAX AltitudeM1
			MAX-ACCESS read-only
			STATUS current
			DESCRIPTION
				"GNSS receiver reported altitude"
		::= { gps3003c03v1Entry 25 }

		-- 1.3.6.1.4.1.10106.3.101291.1.1.27
		gps3003c03v1IpAdd0 OBJECT-TYPE
			SYNTAX Uint8
			MAX-ACCESS read-write
			STATUS current
			DESCRIPTION
				"Unicast IP address (0)"
		::= { gps3003c03v1Entry 27 }

		-- 1.3.6.1.4.1.10106.3.101291.1.1.29
		gps3003c03v1IpAdd1 OBJECT-TYPE
			SYNTAX Uint8
			MAX-ACCESS read-write
			STATUS current
			DESCRIPTION
				"Unicast IP address (1)"
		::= { gps3003c03v1Entry 29 }

		-- 1.3.6.1.4.1.10106.3.101291.1.1.31
		gps3003c03v1IpAdd2 OBJECT-TYPE
			SYNTAX Uint8
			MAX-ACCESS read-write
			STATUS current
			DESCRIPTION
				"Unicast IP address (2)"
		::= { gps3003c03v1Entry 31 }

		-- 1.3.6.1.4.1.10106.3.101291.1.1.33
		gps3003c03v1IpAdd3 OBJECT-TYPE
			SYNTAX Uint8
			MAX-ACCESS read-write
			STATUS current
			DESCRIPTION
				"Unicast IP address (3)"
		::= { gps3003c03v1Entry 33 }

		-- 1.3.6.1.4.1.10106.3.101291.1.1.35
		gps3003c03v1IpMask0 OBJECT-TYPE
			SYNTAX Uint8
			MAX-ACCESS read-write
			STATUS current
			DESCRIPTION
				"IP mask (0)"
		::= { gps3003c03v1Entry 35 }

		-- 1.3.6.1.4.1.10106.3.101291.1.1.37
		gps3003c03v1IpMask1 OBJECT-TYPE
			SYNTAX Uint8
			MAX-ACCESS read-write
			STATUS current
			DESCRIPTION
				"IP mask (1)"
		::= { gps3003c03v1Entry 37 }

		-- 1.3.6.1.4.1.10106.3.101291.1.1.39
		gps3003c03v1IpMask2 OBJECT-TYPE
			SYNTAX Uint8
			MAX-ACCESS read-write
			STATUS current
			DESCRIPTION
				"IP mask (2)"
		::= { gps3003c03v1Entry 39 }

		-- 1.3.6.1.4.1.10106.3.101291.1.1.41
		gps3003c03v1IpMask3 OBJECT-TYPE
			SYNTAX Uint8
			MAX-ACCESS read-write
			STATUS current
			DESCRIPTION
				"IP mask (3)"
		::= { gps3003c03v1Entry 41 }

		-- 1.3.6.1.4.1.10106.3.101291.1.1.43
		gps3003c03v1IpGway0 OBJECT-TYPE
			SYNTAX Uint8
			MAX-ACCESS read-write
			STATUS current
			DESCRIPTION
				"Gateway IP address (0)"
		::= { gps3003c03v1Entry 43 }

		-- 1.3.6.1.4.1.10106.3.101291.1.1.45
		gps3003c03v1IpGway1 OBJECT-TYPE
			SYNTAX Uint8
			MAX-ACCESS read-write
			STATUS current
			DESCRIPTION
				"Gateway IP address (1)"
		::= { gps3003c03v1Entry 45 }

		-- 1.3.6.1.4.1.10106.3.101291.1.1.47
		gps3003c03v1IpGway2 OBJECT-TYPE
			SYNTAX Uint8
			MAX-ACCESS read-write
			STATUS current
			DESCRIPTION
				"Gateway IP address (2)"
		::= { gps3003c03v1Entry 47 }

		-- 1.3.6.1.4.1.10106.3.101291.1.1.49
		gps3003c03v1IpGway3 OBJECT-TYPE
			SYNTAX Uint8
			MAX-ACCESS read-write
			STATUS current
			DESCRIPTION
				"Gateway IP address (3)"
		::= { gps3003c03v1Entry 49 }

		-- 1.3.6.1.4.1.10106.3.101291.1.1.51
		gps3003c03v1Profile OBJECT-TYPE
			SYNTAX PtpProfile
			MAX-ACCESS read-write
			STATUS current
			DESCRIPTION
				"Allows loading default values of a PTP profile"
		::= { gps3003c03v1Entry 51 }

		-- 1.3.6.1.4.1.10106.3.101291.1.1.53
		gps3003c03v1DelayMechanism OBJECT-TYPE
			SYNTAX PtpDelayMech
			MAX-ACCESS read-write
			STATUS current
			DESCRIPTION
				"Allows selecting the delay mechanism"
		::= { gps3003c03v1Entry 53 }

		-- 1.3.6.1.4.1.10106.3.101291.1.1.55
		gps3003c03v1Priority1 OBJECT-TYPE
			SYNTAX Uint8
			MAX-ACCESS read-write
			STATUS current
			DESCRIPTION
				"Allows selecting the Priority1 attribute of the local clock. It is used in the best master selection algorithm"
		::= { gps3003c03v1Entry 55 }

		-- 1.3.6.1.4.1.10106.3.101291.1.1.57
		gps3003c03v1Priority2 OBJECT-TYPE
			SYNTAX Uint8
			MAX-ACCESS read-write
			STATUS current
			DESCRIPTION
				"Allows selecting the Priority2 attribute of the local clock. It is used in the best master selection algorithm"
		::= { gps3003c03v1Entry 57 }

		-- 1.3.6.1.4.1.10106.3.101291.1.1.59
		gps3003c03v1DomainNumber OBJECT-TYPE
			SYNTAX Uint8
			MAX-ACCESS read-write
			STATUS current
			DESCRIPTION
				"Allows selecting the Domanin number attribute of the local clock"
		::= { gps3003c03v1Entry 59 }

		-- 1.3.6.1.4.1.10106.3.101291.1.1.61
		gps3003c03v1LogAnnounceInt OBJECT-TYPE
			SYNTAX PtpInterval
			MAX-ACCESS read-write
			STATUS current
			DESCRIPTION
				"Allows selecting the mean interval between Announce messages"
		::= { gps3003c03v1Entry 61 }

		-- 1.3.6.1.4.1.10106.3.101291.1.1.63
		gps3003c03v1LogSyncInt OBJECT-TYPE
			SYNTAX PtpInterval
			MAX-ACCESS read-write
			STATUS current
			DESCRIPTION
				"Allows selecting the mean interval between Sync messages"
		::= { gps3003c03v1Entry 63 }

		-- 1.3.6.1.4.1.10106.3.101291.1.1.65
		gps3003c03v1LogMinDRInt OBJECT-TYPE
			SYNTAX PtpInterval
			MAX-ACCESS read-write
			STATUS current
			DESCRIPTION
				"Allows selecting the minimum mean interval between Delay_Req messages"
		::= { gps3003c03v1Entry 65 }

		-- 1.3.6.1.4.1.10106.3.101291.1.1.67
		gps3003c03v1LogMinPdRInt OBJECT-TYPE
			SYNTAX PtpInterval
			MAX-ACCESS read-write
			STATUS current
			DESCRIPTION
				"Allows selecting the minimum mean interval between Pdelay_Req messages"
		::= { gps3003c03v1Entry 67 }

		-- 1.3.6.1.4.1.10106.3.101291.1.1.69
		gps3003c03v1AnnounceRTout OBJECT-TYPE
			SYNTAX Uint4
			MAX-ACCESS read-write
			STATUS current
			DESCRIPTION
				"Allows selecting the number of missed Announce messages before the last Announce messages expires"
		::= { gps3003c03v1Entry 69 }

		-- 1.3.6.1.4.1.10106.3.101291.1.1.71
		gps3003c03v1ClockClass OBJECT-TYPE
			SYNTAX Uint8
			MAX-ACCESS read-only
			STATUS current
			DESCRIPTION
				"Indicates the value of the ClockClass attribute of the local clock"
		::= { gps3003c03v1Entry 71 }

		-- 1.3.6.1.4.1.10106.3.101291.1.1.73
		gps3003c03v1PtpState OBJECT-TYPE
			SYNTAX PtpState
			MAX-ACCESS read-only
			STATUS current
			DESCRIPTION
				"Indicates the PTP state"
		::= { gps3003c03v1Entry 73 }

		-- 1.3.6.1.4.1.10106.3.101291.1.1.75
		gps3003c03v1GnssLos OBJECT-TYPE
			SYNTAX BitFail
			MAX-ACCESS read-only
			STATUS current
			DESCRIPTION
				"GNSS loss of signal. To be cleared it has to be for 30 s in in 3D-FIX or Time mode"
		::= { gps3003c03v1Entry 75 }

		-- 1.3.6.1.4.1.10106.3.101291.1.1.76
		gps3003c03v1GnssLosTrapEnable OBJECT-TYPE
			SYNTAX AlarmEnable
			MAX-ACCESS read-write
			STATUS current
			DESCRIPTION
				"GNSS loss of signal. To be cleared it has to be for 30 s in in 3D-FIX or Time mode Trap Enable"
		::= { gps3003c03v1Entry 76 }

		-- 1.3.6.1.4.1.10106.3.101291.1.1.77
		gps3003c03v1GnssPpsLos OBJECT-TYPE
			SYNTAX BitFail
			MAX-ACCESS read-only
			STATUS current
			DESCRIPTION
				"GNSS loss of PPS. It is cleared when the error of the PPS delivered by GNSS module is less than 5 ns. It is set when the delay is greater than 50 ns"
		::= { gps3003c03v1Entry 77 }

		-- 1.3.6.1.4.1.10106.3.101291.1.1.78
		gps3003c03v1GnssPpsLosTrapEnable OBJECT-TYPE
			SYNTAX AlarmEnable
			MAX-ACCESS read-write
			STATUS current
			DESCRIPTION
				"GNSS loss of PPS. It is cleared when the error of the PPS delivered by GNSS module is less than 5 ns. It is set when the delay is greater than 50 ns Trap Enable"
		::= { gps3003c03v1Entry 78 }

		-- 1.3.6.1.4.1.10106.3.101291.1.1.79
		gps3003c03v1GnssUnlock OBJECT-TYPE
			SYNTAX BitFail
			MAX-ACCESS read-only
			STATUS current
			DESCRIPTION
				"GNSS PPS unlock. It is cleared when the error of the output PPS is less than 10 ns. It is set when the error is greater than 100 ns."
		::= { gps3003c03v1Entry 79 }

		-- 1.3.6.1.4.1.10106.3.101291.1.1.80
		gps3003c03v1GnssUnlockTrapEnable OBJECT-TYPE
			SYNTAX AlarmEnable
			MAX-ACCESS read-write
			STATUS current
			DESCRIPTION
				"GNSS PPS unlock. It is cleared when the error of the output PPS is less than 10 ns. It is set when the error is greater than 100 ns. Trap Enable"
		::= { gps3003c03v1Entry 80 }

		-- 1.3.6.1.4.1.10106.3.101291.1.1.81
		gps3003c03v1GnssPpsErr OBJECT-TYPE
			SYNTAX BitFail
			MAX-ACCESS read-only
			STATUS current
			DESCRIPTION
				"GNSS pulse error. It is cleared when the error of the output PPS is less than the value specified in 'GNSS valid PPS margin'. It is set when the error is greater than this value."
		::= { gps3003c03v1Entry 81 }

		-- 1.3.6.1.4.1.10106.3.101291.1.1.82
		gps3003c03v1GnssPpsErrTrapEnable OBJECT-TYPE
			SYNTAX AlarmEnable
			MAX-ACCESS read-write
			STATUS current
			DESCRIPTION
				"GNSS pulse error. It is cleared when the error of the output PPS is less than the value specified in 'GNSS valid PPS margin'. It is set when the error is greater than this value. Trap Enable"
		::= { gps3003c03v1Entry 82 }

		-- 1.3.6.1.4.1.10106.3.101291.1.1.83
		gps3003c03v1PtpLos OBJECT-TYPE
			SYNTAX BitFail
			MAX-ACCESS read-only
			STATUS current
			DESCRIPTION
				"PTP loss of signal.It is cleared when the PTP module is in Slave or Uncalibrated mode"
		::= { gps3003c03v1Entry 83 }

		-- 1.3.6.1.4.1.10106.3.101291.1.1.84
		gps3003c03v1PtpLosTrapEnable OBJECT-TYPE
			SYNTAX AlarmEnable
			MAX-ACCESS read-write
			STATUS current
			DESCRIPTION
				"PTP loss of signal.It is cleared when the PTP module is in Slave or Uncalibrated mode Trap Enable"
		::= { gps3003c03v1Entry 84 }

		-- 1.3.6.1.4.1.10106.3.101291.1.1.85
		gps3003c03v1PtpPpsLos OBJECT-TYPE
			SYNTAX BitFail
			MAX-ACCESS read-only
			STATUS current
			DESCRIPTION
				"PTP loss of PPS. It is cleared after 30 s receiving a valid PPS from PTP module"
		::= { gps3003c03v1Entry 85 }

		-- 1.3.6.1.4.1.10106.3.101291.1.1.86
		gps3003c03v1PtpPpsLosTrapEnable OBJECT-TYPE
			SYNTAX AlarmEnable
			MAX-ACCESS read-write
			STATUS current
			DESCRIPTION
				"PTP loss of PPS. It is cleared after 30 s receiving a valid PPS from PTP module Trap Enable"
		::= { gps3003c03v1Entry 86 }

		-- 1.3.6.1.4.1.10106.3.101291.1.1.87
		gps3003c03v1PtpUnlock OBJECT-TYPE
			SYNTAX BitFail
			MAX-ACCESS read-only
			STATUS current
			DESCRIPTION
				"PTP PPS unlock. It is cleared when the error of the output PPS is less than 25 ns. It is set when the error is greater than 250 ns."
		::= { gps3003c03v1Entry 87 }

		-- 1.3.6.1.4.1.10106.3.101291.1.1.88
		gps3003c03v1PtpUnlockTrapEnable OBJECT-TYPE
			SYNTAX AlarmEnable
			MAX-ACCESS read-write
			STATUS current
			DESCRIPTION
				"PTP PPS unlock. It is cleared when the error of the output PPS is less than 25 ns. It is set when the error is greater than 250 ns. Trap Enable"
		::= { gps3003c03v1Entry 88 }

		-- 1.3.6.1.4.1.10106.3.101291.1.1.89
		gps3003c03v1PtpPpsErr OBJECT-TYPE
			SYNTAX BitFail
			MAX-ACCESS read-only
			STATUS current
			DESCRIPTION
				"PTP PPS error. It is cleared when the error of the output PPS is less than the value specified in 'PTP valid PPS margin'. It is set when the error is greater than this value."
		::= { gps3003c03v1Entry 89 }

		-- 1.3.6.1.4.1.10106.3.101291.1.1.90
		gps3003c03v1PtpPpsErrTrapEnable OBJECT-TYPE
			SYNTAX AlarmEnable
			MAX-ACCESS read-write
			STATUS current
			DESCRIPTION
				"PTP PPS error. It is cleared when the error of the output PPS is less than the value specified in 'PTP valid PPS margin'. It is set when the error is greater than this value. Trap Enable"
		::= { gps3003c03v1Entry 90 }

		-- 1.3.6.1.4.1.10106.3.101291.1.1.91
		gps3003c03v1SyncState OBJECT-TYPE
			SYNTAX Gps2SyncState
			MAX-ACCESS read-only
			STATUS current
			DESCRIPTION
				"Indicates the synchronization state"
		::= { gps3003c03v1Entry 91 }

		-- 1.3.6.1.4.1.10106.3.101291.1.1.92
		gps3003c03v1SyncStateTrapEnable OBJECT-TYPE
			SYNTAX AlarmEnable
			MAX-ACCESS read-write
			STATUS current
			DESCRIPTION
				"Indicates the synchronization state Trap Enable"
		::= { gps3003c03v1Entry 92 }

		-- 1.3.6.1.4.1.10106.3.101291.1.1.93
		gps3003c03v1ValidPps OBJECT-TYPE
			SYNTAX Bit0No1Yes
			MAX-ACCESS read-only
			STATUS current
			DESCRIPTION
				"Indicates that the internally generated PPS signal has been phase aligned with an external reference (GNSS or PTP)"
		::= { gps3003c03v1Entry 93 }

		-- 1.3.6.1.4.1.10106.3.101291.1.1.94
		gps3003c03v1ValidPpsTrapEnable OBJECT-TYPE
			SYNTAX AlarmEnable
			MAX-ACCESS read-write
			STATUS current
			DESCRIPTION
				"Indicates that the internally generated PPS signal has been phase aligned with an external reference (GNSS or PTP) Trap Enable"
		::= { gps3003c03v1Entry 94 }

		-- 1.3.6.1.4.1.10106.3.101291.1.1.95
		gps3003c03v1ModuleActive OBJECT-TYPE
			SYNTAX Bit0No1Yes
			MAX-ACCESS read-only
			STATUS current
			DESCRIPTION
				"Indicates that this module is the one that provides the reference signals"
		::= { gps3003c03v1Entry 95 }

		-- 1.3.6.1.4.1.10106.3.101291.1.1.96
		gps3003c03v1ModuleActiveTrapEnable OBJECT-TYPE
			SYNTAX AlarmEnable
			MAX-ACCESS read-write
			STATUS current
			DESCRIPTION
				"Indicates that this module is the one that provides the reference signals Trap Enable"
		::= { gps3003c03v1Entry 96 }

		-- 1.3.6.1.4.1.10106.3.101291.1.1.97
		gps3003c03v1RedSyncState OBJECT-TYPE
			SYNTAX Gps2SyncState
			MAX-ACCESS read-only
			STATUS current
			DESCRIPTION
				"Indicates the redundant module's synchronization state"
		::= { gps3003c03v1Entry 97 }

		-- 1.3.6.1.4.1.10106.3.101291.1.1.98
		gps3003c03v1RedSyncStateTrapEnable OBJECT-TYPE
			SYNTAX AlarmEnable
			MAX-ACCESS read-write
			STATUS current
			DESCRIPTION
				"Indicates the redundant module's synchronization state Trap Enable"
		::= { gps3003c03v1Entry 98 }

		-- 1.3.6.1.4.1.10106.3.101291.1.1.99
		gps3003c03v1RedModule OBJECT-TYPE
			SYNTAX Bit0No1Yes
			MAX-ACCESS read-only
			STATUS current
			DESCRIPTION
				"Indicates if the redundant module is present"
		::= { gps3003c03v1Entry 99 }

		-- 1.3.6.1.4.1.10106.3.101291.1.1.100
		gps3003c03v1RedModuleTrapEnable OBJECT-TYPE
			SYNTAX AlarmEnable
			MAX-ACCESS read-write
			STATUS current
			DESCRIPTION
				"Indicates if the redundant module is present Trap Enable"
		::= { gps3003c03v1Entry 100 }

		-- 1.3.6.1.4.1.10106.3.101291.1.1.101
		gps3003c03v1FixMode OBJECT-TYPE
			SYNTAX Gps2FixMode
			MAX-ACCESS read-only
			STATUS current
			DESCRIPTION
				"GNSS receiver module satellite tracking mode"
		::= { gps3003c03v1Entry 101 }

		-- 1.3.6.1.4.1.10106.3.101291.1.1.102
		gps3003c03v1FixModeTrapEnable OBJECT-TYPE
			SYNTAX AlarmEnable
			MAX-ACCESS read-write
			STATUS current
			DESCRIPTION
				"GNSS receiver module satellite tracking mode Trap Enable"
		::= { gps3003c03v1Entry 102 }

		-- 1.3.6.1.4.1.10106.3.101291.1.1.103
		gps3003c03v1DiffMode OBJECT-TYPE
			SYNTAX Bit0No1Yes
			MAX-ACCESS read-only
			STATUS current
			DESCRIPTION
				"GNSS receiver receives correction data and uses them to improve provided solution"
		::= { gps3003c03v1Entry 103 }

		-- 1.3.6.1.4.1.10106.3.101291.1.1.105
		gps3003c03v1NumUsedSats OBJECT-TYPE
			SYNTAX Uint8
			MAX-ACCESS read-only
			STATUS current
			DESCRIPTION
				"Number of GNSS used in current fix"
		::= { gps3003c03v1Entry 105 }

		-- 1.3.6.1.4.1.10106.3.101291.1.1.107
		gps3003c03v1CN0Max OBJECT-TYPE
			SYNTAX LevelDbHz
			MAX-ACCESS read-only
			STATUS current
			DESCRIPTION
				"Estimated carrier to noise ratio for the best satellite in tracking"
		::= { gps3003c03v1Entry 107 }

		-- 1.3.6.1.4.1.10106.3.101291.1.1.109
		gps3003c03v1PositionAcc OBJECT-TYPE
			SYNTAX AltitudeM1
			MAX-ACCESS read-only
			STATUS current
			DESCRIPTION
				"Estimated position accuracy"
		::= { gps3003c03v1Entry 109 }

		-- 1.3.6.1.4.1.10106.3.101291.1.1.111
		gps3003c03v1TimTosOffset OBJECT-TYPE
			SYNTAX TimeX1Ns
			MAX-ACCESS read-only
			STATUS current
			DESCRIPTION
				"Estimated GNSS module PPS error"
		::= { gps3003c03v1Entry 111 }

		-- 1.3.6.1.4.1.10106.3.101291.1.1.113
		gps3003c03v1SurveyTout OBJECT-TYPE
			SYNTAX TimeS2
			MAX-ACCESS read-only
			STATUS current
			DESCRIPTION
				"Time to exit Survey-in"
		::= { gps3003c03v1Entry 113 }

		-- 1.3.6.1.4.1.10106.3.101291.1.1.115
		gps3003c03v1HoldoverTime OBJECT-TYPE
			SYNTAX GpsHoldovrTime
			MAX-ACCESS read-only
			STATUS current
			DESCRIPTION
				"Holdover time"
		::= { gps3003c03v1Entry 115 }

		-- 1.3.6.1.4.1.10106.3.101291.1.1.117
		gps3003c03v1PowerStat OBJECT-TYPE
			SYNTAX Bit0Ok1Fail
			MAX-ACCESS read-only
			STATUS current
			DESCRIPTION
				"Indicates the power supply status"
		::= { gps3003c03v1Entry 117 }

		-- 1.3.6.1.4.1.10106.3.101291.1.1.118
		gps3003c03v1PowerStatTrapEnable OBJECT-TYPE
			SYNTAX AlarmEnable
			MAX-ACCESS read-write
			STATUS current
			DESCRIPTION
				"Indicates the power supply status Trap Enable"
		::= { gps3003c03v1Entry 118 }

		-- 1.3.6.1.4.1.10106.3.101291.1.1.119
		gps3003c03v1AntennaStat OBJECT-TYPE
			SYNTAX GpsAntenaStat
			MAX-ACCESS read-only
			STATUS current
			DESCRIPTION
				"Indicates the antenna connection status"
		::= { gps3003c03v1Entry 119 }

		-- 1.3.6.1.4.1.10106.3.101291.1.1.120
		gps3003c03v1AntennaStatTrapEnable OBJECT-TYPE
			SYNTAX AlarmEnable
			MAX-ACCESS read-write
			STATUS current
			DESCRIPTION
				"Indicates the antenna connection status Trap Enable"
		::= { gps3003c03v1Entry 120 }

		-- 1.3.6.1.4.1.10106.3.101291.1.1.121
		gps3003c03v1EthLink OBJECT-TYPE
			SYNTAX Bit0No1Yes
			MAX-ACCESS read-only
			STATUS current
			DESCRIPTION
				"Indicates that the Ethernet link is OK"
		::= { gps3003c03v1Entry 121 }

		-- 1.3.6.1.4.1.10106.3.101291.1.1.122
		gps3003c03v1EthLinkTrapEnable OBJECT-TYPE
			SYNTAX AlarmEnable
			MAX-ACCESS read-write
			STATUS current
			DESCRIPTION
				"Indicates that the Ethernet link is OK Trap Enable"
		::= { gps3003c03v1Entry 122 }

		-- 1.3.6.1.4.1.10106.3.101291.1.1.123
		gps3003c03v1AdjustingFreq OBJECT-TYPE
			SYNTAX Bit0No1Yes
			MAX-ACCESS read-only
			STATUS current
			DESCRIPTION
				"Indicates that the module is adjusting the frequency"
		::= { gps3003c03v1Entry 123 }

		-- 1.3.6.1.4.1.10106.3.101291.1.1.125
		gps3003c03v1OcxoWarInProg OBJECT-TYPE
			SYNTAX Bit0No1Yes
			MAX-ACCESS read-only
			STATUS current
			DESCRIPTION
				"Indicates that the OCXO warming is in progress"
		::= { gps3003c03v1Entry 125 }

		-- 1.3.6.1.4.1.10106.3.101291.1.1.127
		gps3003c03v1OnePpsStat OBJECT-TYPE
			SYNTAX Bit0Ina1Act
			MAX-ACCESS read-only
			STATUS current
			DESCRIPTION
				"Indicates that the module is delivering a valid PPS"
		::= { gps3003c03v1Entry 127 }

		-- 1.3.6.1.4.1.10106.3.101291.1.1.128
		gps3003c03v1OnePpsStatTrapEnable OBJECT-TYPE
			SYNTAX AlarmEnable
			MAX-ACCESS read-write
			STATUS current
			DESCRIPTION
				"Indicates that the module is delivering a valid PPS Trap Enable"
		::= { gps3003c03v1Entry 128 }

		-- 1.3.6.1.4.1.10106.3.101291.1.1.129
		gps3003c03v1OnePps OBJECT-TYPE
			SYNTAX BitPps
			MAX-ACCESS read-only
			STATUS current
			DESCRIPTION
				"One pulse per second signal"
		::= { gps3003c03v1Entry 129 }

		-- 1.3.6.1.4.1.10106.3.101291.1.1.131
		gps3003c03v1GnssDelay OBJECT-TYPE
			SYNTAX TimeX1p25Ns
			MAX-ACCESS read-only
			STATUS current
			DESCRIPTION
				"PPS delay relative to GNSS"
		::= { gps3003c03v1Entry 131 }

		-- 1.3.6.1.4.1.10106.3.101291.1.1.133
		gps3003c03v1PtpDelay OBJECT-TYPE
			SYNTAX TimeX1p25Ns
			MAX-ACCESS read-only
			STATUS current
			DESCRIPTION
				"PPS delay relative to PTP"
		::= { gps3003c03v1Entry 133 }

		-- 1.3.6.1.4.1.10106.3.101291.1.1.135
		gps3003c03v1SerialNo OBJECT-TYPE
			SYNTAX SerialNo
			MAX-ACCESS read-only
			STATUS current
			DESCRIPTION
				"Serial number"
		::= { gps3003c03v1Entry 135 }

		-- 1.3.6.1.4.1.10106.3.101291.1.1.137
		gps3003c03v1GnssModVer OBJECT-TYPE
			SYNTAX UbloxF9tVer
			MAX-ACCESS read-only
			STATUS current
			DESCRIPTION
				"GNSS module version"
		::= { gps3003c03v1Entry 137 }

		-- 1.3.6.1.4.1.10106.3.101291.1.1.139
		gps3003c03v1IpNtpSrv0 OBJECT-TYPE
			SYNTAX Uint8
			MAX-ACCESS read-write
			STATUS current
			DESCRIPTION
				"NTP server IP address (0)"
		::= { gps3003c03v1Entry 139 }

		-- 1.3.6.1.4.1.10106.3.101291.1.1.141
		gps3003c03v1IpNtpSrv1 OBJECT-TYPE
			SYNTAX Uint8
			MAX-ACCESS read-write
			STATUS current
			DESCRIPTION
				"NTP server IP address (1)"
		::= { gps3003c03v1Entry 141 }

		-- 1.3.6.1.4.1.10106.3.101291.1.1.143
		gps3003c03v1IpNtpSrv2 OBJECT-TYPE
			SYNTAX Uint8
			MAX-ACCESS read-write
			STATUS current
			DESCRIPTION
				"NTP server IP address (2)"
		::= { gps3003c03v1Entry 143 }

		-- 1.3.6.1.4.1.10106.3.101291.1.1.145
		gps3003c03v1IpNtpSrv3 OBJECT-TYPE
			SYNTAX Uint8
			MAX-ACCESS read-write
			STATUS current
			DESCRIPTION
				"NTP server IP address (3)"
		::= { gps3003c03v1Entry 145 }

		-- 1.3.6.1.4.1.10106.3.101291.1.1.147
		gps3003c03v1TimeDateOk OBJECT-TYPE
			SYNTAX BitFailN
			MAX-ACCESS read-only
			STATUS current
			DESCRIPTION
				"Time and date OK"
		::= { gps3003c03v1Entry 147 }

		-- 1.3.6.1.4.1.10106.3.587701
		gps3003c04v1 OBJECT IDENTIFIER ::= { albalaProducts 587701 }

		-- 1.3.6.1.4.1.10106.3.587701.1
		gps3003c04v1Table  OBJECT-TYPE
			SYNTAX SEQUENCE OF Gps3003c04v1Entry
			MAX-ACCESS not-accessible
			STATUS current
			DESCRIPTION
				"Module  GPS3003C04V1 Table"
			::= { gps3003c04v1 1 }

		-- 1.3.6.1.4.1.10106.3.587701.1.1
		gps3003c04v1Entry  OBJECT-TYPE
			SYNTAX Gps3003c04v1Entry
			MAX-ACCESS not-accessible
			STATUS current
			DESCRIPTION
				"Module GPS3003C04V1 Entry"
			INDEX { gps3003c04v1Index }
			::= { gps3003c04v1Table 1 }

			Gps3003c04v1Entry ::=
			SEQUENCE {
				gps3003c04v1Index
				ModuleIndex,
				gps3003c04v1SyncMode
				Gps2SyncMode,
				gps3003c04v1PtpSrvEnable
				Bit0No1Yes,
				gps3003c04v1PtpCliEnable
				Bit0No1Yes,
				gps3003c04v1InfoTimePps
				Bit0No1Yes,
				gps3003c04v1PtpDelayAsym
				TimeX1Ns,
				gps3003c04v1HoldoverTout
				GpsHoldovrTime,
				gps3003c04v1CableDelay
				DelayX1Ns,
				gps3003c04v1FTimeDriftEst
				Gps2FrqTimDrf,
				gps3003c04v1FTempDriftEst
				Gps2FrqTemDrf,
				gps3003c04v1Longitude
				AngleDeg1,
				gps3003c04v1Latitude
				AngleDeg1,
				gps3003c04v1Altitude
				AltitudeM1,
				gps3003c04v1IpAdd0
				Uint8,
				gps3003c04v1IpAdd1
				Uint8,
				gps3003c04v1IpAdd2
				Uint8,
				gps3003c04v1IpAdd3
				Uint8,
				gps3003c04v1IpMask0
				Uint8,
				gps3003c04v1IpMask1
				Uint8,
				gps3003c04v1IpMask2
				Uint8,
				gps3003c04v1IpMask3
				Uint8,
				gps3003c04v1IpGway0
				Uint8,
				gps3003c04v1IpGway1
				Uint8,
				gps3003c04v1IpGway2
				Uint8,
				gps3003c04v1IpGway3
				Uint8,
				gps3003c04v1Profile
				PtpProfile,
				gps3003c04v1DelayMechanism
				PtpDelayMech,
				gps3003c04v1Priority1
				Uint8,
				gps3003c04v1Priority2
				Uint8,
				gps3003c04v1DomainNumber
				Uint8,
				gps3003c04v1LogAnnounceInt
				PtpInterval,
				gps3003c04v1LogSyncInt
				PtpInterval,
				gps3003c04v1LogMinDRInt
				PtpInterval,
				gps3003c04v1LogMinPdRInt
				PtpInterval,
				gps3003c04v1AnnounceRTout
				Uint4,
				gps3003c04v1ClockClass
				Uint8,
				gps3003c04v1PtpState
				PtpState,
				gps3003c04v1GnssLos
				BitFail,
				gps3003c04v1GnssLosTrapEnable
				AlarmEnable,
				gps3003c04v1GnssPpsLos
				BitFail,
				gps3003c04v1GnssPpsLosTrapEnable
				AlarmEnable,
				gps3003c04v1GnssUnlock
				BitFail,
				gps3003c04v1GnssUnlockTrapEnable
				AlarmEnable,
				gps3003c04v1GnssPpsErr
				BitFail,
				gps3003c04v1GnssPpsErrTrapEnable
				AlarmEnable,
				gps3003c04v1PtpLos
				BitFail,
				gps3003c04v1PtpLosTrapEnable
				AlarmEnable,
				gps3003c04v1PtpPpsLos
				BitFail,
				gps3003c04v1PtpPpsLosTrapEnable
				AlarmEnable,
				gps3003c04v1PtpUnlock
				BitFail,
				gps3003c04v1PtpUnlockTrapEnable
				AlarmEnable,
				gps3003c04v1PtpPpsErr
				BitFail,
				gps3003c04v1PtpPpsErrTrapEnable
				AlarmEnable,
				gps3003c04v1SyncState
				Gps2SyncState,
				gps3003c04v1SyncStateTrapEnable
				AlarmEnable,
				gps3003c04v1ValidPps
				Bit0No1Yes,
				gps3003c04v1ValidPpsTrapEnable
				AlarmEnable,
				gps3003c04v1ModuleActive
				Bit0No1Yes,
				gps3003c04v1ModuleActiveTrapEnable
				AlarmEnable,
				gps3003c04v1RedSyncState
				Gps2SyncState,
				gps3003c04v1RedSyncStateTrapEnable
				AlarmEnable,
				gps3003c04v1RedModule
				Bit0No1Yes,
				gps3003c04v1RedModuleTrapEnable
				AlarmEnable,
				gps3003c04v1FixMode
				Gps2FixMode,
				gps3003c04v1FixModeTrapEnable
				AlarmEnable,
				gps3003c04v1DiffMode
				Bit0No1Yes,
				gps3003c04v1NumUsedSats
				Uint8,
				gps3003c04v1CN0Max
				LevelDbHz,
				gps3003c04v1PositionAcc
				AltitudeM1,
				gps3003c04v1TimTosOffset
				TimeX1Ns,
				gps3003c04v1SurveyTout
				TimeS2,
				gps3003c04v1HoldoverTime
				GpsHoldovrTime,
				gps3003c04v1PowerStat
				Bit0Ok1Fail,
				gps3003c04v1PowerStatTrapEnable
				AlarmEnable,
				gps3003c04v1AntennaStat
				GpsAntenaStat,
				gps3003c04v1AntennaStatTrapEnable
				AlarmEnable,
				gps3003c04v1EthLink
				Bit0No1Yes,
				gps3003c04v1EthLinkTrapEnable
				AlarmEnable,
				gps3003c04v1AdjustingFreq
				Bit0No1Yes,
				gps3003c04v1OcxoWarInProg
				Bit0No1Yes,
				gps3003c04v1OnePpsStat
				Bit0Ina1Act,
				gps3003c04v1OnePpsStatTrapEnable
				AlarmEnable,
				gps3003c04v1OnePps
				BitPps,
				gps3003c04v1GnssDelay
				TimeX1p25Ns,
				gps3003c04v1PtpDelay
				TimeX1p25Ns,
				gps3003c04v1SerialNo
				SerialNo,
				gps3003c04v1GnssModVer
				UbloxF9tVer,
				gps3003c04v1IpNtpSrv0
				Uint8,
				gps3003c04v1IpNtpSrv1
				Uint8,
				gps3003c04v1IpNtpSrv2
				Uint8,
				gps3003c04v1IpNtpSrv3
				Uint8,
				gps3003c04v1TimeDateOk
				BitFailN
			 }

		-- 1.3.6.1.4.1.10106.3.101291.1.1.1
		gps3003c04v1Index OBJECT-TYPE
			SYNTAX ModuleIndex
			MAX-ACCESS read-only
			STATUS current
			DESCRIPTION
				"Index of GPS3003C04V1 Table"
		::= { gps3003c04v1Entry 1 }

		-- 1.3.6.1.4.1.10106.3.101291.1.1.3
		gps3003c04v1SyncMode OBJECT-TYPE
			SYNTAX Gps2SyncMode
			MAX-ACCESS read-write
			STATUS current
			DESCRIPTION
				"Allows selecting the synchronization mode"
		::= { gps3003c04v1Entry 3 }

		-- 1.3.6.1.4.1.10106.3.101291.1.1.5
		gps3003c04v1PtpSrvEnable OBJECT-TYPE
			SYNTAX Bit0No1Yes
			MAX-ACCESS read-write
			STATUS current
			DESCRIPTION
				"Allows enabling the PTP server when Sync mode is GNSS"
		::= { gps3003c04v1Entry 5 }

		-- 1.3.6.1.4.1.10106.3.101291.1.1.7
		gps3003c04v1PtpCliEnable OBJECT-TYPE
			SYNTAX Bit0No1Yes
			MAX-ACCESS read-write
			STATUS current
			DESCRIPTION
				"Allows enabling the PTP client for logging when Sync mode is GNSS"
		::= { gps3003c04v1Entry 7 }

		-- 1.3.6.1.4.1.10106.3.101291.1.1.9
		gps3003c04v1InfoTimePps OBJECT-TYPE
			SYNTAX Bit0No1Yes
			MAX-ACCESS read-write
			STATUS current
			DESCRIPTION
				"Allows embedding PTP timestamp in 1 PPS signal"
		::= { gps3003c04v1Entry 9 }

		-- 1.3.6.1.4.1.10106.3.101291.1.1.11
		gps3003c04v1PtpDelayAsym OBJECT-TYPE
			SYNTAX TimeX1Ns
			MAX-ACCESS read-write
			STATUS current
			DESCRIPTION
				"Allows compensating the PTP delay asymmetry"
		::= { gps3003c04v1Entry 11 }

		-- 1.3.6.1.4.1.10106.3.101291.1.1.13
		gps3003c04v1HoldoverTout OBJECT-TYPE
			SYNTAX GpsHoldovrTime
			MAX-ACCESS read-write
			STATUS current
			DESCRIPTION
				"Allows selecting the maximum holdover time"
		::= { gps3003c04v1Entry 13 }

		-- 1.3.6.1.4.1.10106.3.101291.1.1.15
		gps3003c04v1CableDelay OBJECT-TYPE
			SYNTAX DelayX1Ns
			MAX-ACCESS read-write
			STATUS current
			DESCRIPTION
				"Allows compensating the antenna cable delay"
		::= { gps3003c04v1Entry 15 }

		-- 1.3.6.1.4.1.10106.3.101291.1.1.17
		gps3003c04v1FTimeDriftEst OBJECT-TYPE
			SYNTAX Gps2FrqTimDrf
			MAX-ACCESS read-only
			STATUS current
			DESCRIPTION
				"Frequency time drift estimation"
		::= { gps3003c04v1Entry 17 }

		-- 1.3.6.1.4.1.10106.3.101291.1.1.19
		gps3003c04v1FTempDriftEst OBJECT-TYPE
			SYNTAX Gps2FrqTemDrf
			MAX-ACCESS read-only
			STATUS current
			DESCRIPTION
				"Frequency temperature drift estimation"
		::= { gps3003c04v1Entry 19 }

		-- 1.3.6.1.4.1.10106.3.101291.1.1.21
		gps3003c04v1Longitude OBJECT-TYPE
			SYNTAX AngleDeg1
			MAX-ACCESS read-only
			STATUS current
			DESCRIPTION
				"GNSS receiver reported longitude"
		::= { gps3003c04v1Entry 21 }

		-- 1.3.6.1.4.1.10106.3.101291.1.1.23
		gps3003c04v1Latitude OBJECT-TYPE
			SYNTAX AngleDeg1
			MAX-ACCESS read-only
			STATUS current
			DESCRIPTION
				"GNSS receiver reported latitude"
		::= { gps3003c04v1Entry 23 }

		-- 1.3.6.1.4.1.10106.3.101291.1.1.25
		gps3003c04v1Altitude OBJECT-TYPE
			SYNTAX AltitudeM1
			MAX-ACCESS read-only
			STATUS current
			DESCRIPTION
				"GNSS receiver reported altitude"
		::= { gps3003c04v1Entry 25 }

		-- 1.3.6.1.4.1.10106.3.101291.1.1.27
		gps3003c04v1IpAdd0 OBJECT-TYPE
			SYNTAX Uint8
			MAX-ACCESS read-write
			STATUS current
			DESCRIPTION
				"Unicast IP address (0)"
		::= { gps3003c04v1Entry 27 }

		-- 1.3.6.1.4.1.10106.3.101291.1.1.29
		gps3003c04v1IpAdd1 OBJECT-TYPE
			SYNTAX Uint8
			MAX-ACCESS read-write
			STATUS current
			DESCRIPTION
				"Unicast IP address (1)"
		::= { gps3003c04v1Entry 29 }

		-- 1.3.6.1.4.1.10106.3.101291.1.1.31
		gps3003c04v1IpAdd2 OBJECT-TYPE
			SYNTAX Uint8
			MAX-ACCESS read-write
			STATUS current
			DESCRIPTION
				"Unicast IP address (2)"
		::= { gps3003c04v1Entry 31 }

		-- 1.3.6.1.4.1.10106.3.101291.1.1.33
		gps3003c04v1IpAdd3 OBJECT-TYPE
			SYNTAX Uint8
			MAX-ACCESS read-write
			STATUS current
			DESCRIPTION
				"Unicast IP address (3)"
		::= { gps3003c04v1Entry 33 }

		-- 1.3.6.1.4.1.10106.3.101291.1.1.35
		gps3003c04v1IpMask0 OBJECT-TYPE
			SYNTAX Uint8
			MAX-ACCESS read-write
			STATUS current
			DESCRIPTION
				"IP mask (0)"
		::= { gps3003c04v1Entry 35 }

		-- 1.3.6.1.4.1.10106.3.101291.1.1.37
		gps3003c04v1IpMask1 OBJECT-TYPE
			SYNTAX Uint8
			MAX-ACCESS read-write
			STATUS current
			DESCRIPTION
				"IP mask (1)"
		::= { gps3003c04v1Entry 37 }

		-- 1.3.6.1.4.1.10106.3.101291.1.1.39
		gps3003c04v1IpMask2 OBJECT-TYPE
			SYNTAX Uint8
			MAX-ACCESS read-write
			STATUS current
			DESCRIPTION
				"IP mask (2)"
		::= { gps3003c04v1Entry 39 }

		-- 1.3.6.1.4.1.10106.3.101291.1.1.41
		gps3003c04v1IpMask3 OBJECT-TYPE
			SYNTAX Uint8
			MAX-ACCESS read-write
			STATUS current
			DESCRIPTION
				"IP mask (3)"
		::= { gps3003c04v1Entry 41 }

		-- 1.3.6.1.4.1.10106.3.101291.1.1.43
		gps3003c04v1IpGway0 OBJECT-TYPE
			SYNTAX Uint8
			MAX-ACCESS read-write
			STATUS current
			DESCRIPTION
				"Gateway IP address (0)"
		::= { gps3003c04v1Entry 43 }

		-- 1.3.6.1.4.1.10106.3.101291.1.1.45
		gps3003c04v1IpGway1 OBJECT-TYPE
			SYNTAX Uint8
			MAX-ACCESS read-write
			STATUS current
			DESCRIPTION
				"Gateway IP address (1)"
		::= { gps3003c04v1Entry 45 }

		-- 1.3.6.1.4.1.10106.3.101291.1.1.47
		gps3003c04v1IpGway2 OBJECT-TYPE
			SYNTAX Uint8
			MAX-ACCESS read-write
			STATUS current
			DESCRIPTION
				"Gateway IP address (2)"
		::= { gps3003c04v1Entry 47 }

		-- 1.3.6.1.4.1.10106.3.101291.1.1.49
		gps3003c04v1IpGway3 OBJECT-TYPE
			SYNTAX Uint8
			MAX-ACCESS read-write
			STATUS current
			DESCRIPTION
				"Gateway IP address (3)"
		::= { gps3003c04v1Entry 49 }

		-- 1.3.6.1.4.1.10106.3.101291.1.1.51
		gps3003c04v1Profile OBJECT-TYPE
			SYNTAX PtpProfile
			MAX-ACCESS read-write
			STATUS current
			DESCRIPTION
				"Allows loading default values of a PTP profile"
		::= { gps3003c04v1Entry 51 }

		-- 1.3.6.1.4.1.10106.3.101291.1.1.53
		gps3003c04v1DelayMechanism OBJECT-TYPE
			SYNTAX PtpDelayMech
			MAX-ACCESS read-write
			STATUS current
			DESCRIPTION
				"Allows selecting the delay mechanism"
		::= { gps3003c04v1Entry 53 }

		-- 1.3.6.1.4.1.10106.3.101291.1.1.55
		gps3003c04v1Priority1 OBJECT-TYPE
			SYNTAX Uint8
			MAX-ACCESS read-write
			STATUS current
			DESCRIPTION
				"Allows selecting the Priority1 attribute of the local clock. It is used in the best master selection algorithm"
		::= { gps3003c04v1Entry 55 }

		-- 1.3.6.1.4.1.10106.3.101291.1.1.57
		gps3003c04v1Priority2 OBJECT-TYPE
			SYNTAX Uint8
			MAX-ACCESS read-write
			STATUS current
			DESCRIPTION
				"Allows selecting the Priority2 attribute of the local clock. It is used in the best master selection algorithm"
		::= { gps3003c04v1Entry 57 }

		-- 1.3.6.1.4.1.10106.3.101291.1.1.59
		gps3003c04v1DomainNumber OBJECT-TYPE
			SYNTAX Uint8
			MAX-ACCESS read-write
			STATUS current
			DESCRIPTION
				"Allows selecting the Domanin number attribute of the local clock"
		::= { gps3003c04v1Entry 59 }

		-- 1.3.6.1.4.1.10106.3.101291.1.1.61
		gps3003c04v1LogAnnounceInt OBJECT-TYPE
			SYNTAX PtpInterval
			MAX-ACCESS read-write
			STATUS current
			DESCRIPTION
				"Allows selecting the mean interval between Announce messages"
		::= { gps3003c04v1Entry 61 }

		-- 1.3.6.1.4.1.10106.3.101291.1.1.63
		gps3003c04v1LogSyncInt OBJECT-TYPE
			SYNTAX PtpInterval
			MAX-ACCESS read-write
			STATUS current
			DESCRIPTION
				"Allows selecting the mean interval between Sync messages"
		::= { gps3003c04v1Entry 63 }

		-- 1.3.6.1.4.1.10106.3.101291.1.1.65
		gps3003c04v1LogMinDRInt OBJECT-TYPE
			SYNTAX PtpInterval
			MAX-ACCESS read-write
			STATUS current
			DESCRIPTION
				"Allows selecting the minimum mean interval between Delay_Req messages"
		::= { gps3003c04v1Entry 65 }

		-- 1.3.6.1.4.1.10106.3.101291.1.1.67
		gps3003c04v1LogMinPdRInt OBJECT-TYPE
			SYNTAX PtpInterval
			MAX-ACCESS read-write
			STATUS current
			DESCRIPTION
				"Allows selecting the minimum mean interval between Pdelay_Req messages"
		::= { gps3003c04v1Entry 67 }

		-- 1.3.6.1.4.1.10106.3.101291.1.1.69
		gps3003c04v1AnnounceRTout OBJECT-TYPE
			SYNTAX Uint4
			MAX-ACCESS read-write
			STATUS current
			DESCRIPTION
				"Allows selecting the number of missed Announce messages before the last Announce messages expires"
		::= { gps3003c04v1Entry 69 }

		-- 1.3.6.1.4.1.10106.3.101291.1.1.71
		gps3003c04v1ClockClass OBJECT-TYPE
			SYNTAX Uint8
			MAX-ACCESS read-only
			STATUS current
			DESCRIPTION
				"Indicates the value of the ClockClass attribute of the local clock"
		::= { gps3003c04v1Entry 71 }

		-- 1.3.6.1.4.1.10106.3.101291.1.1.73
		gps3003c04v1PtpState OBJECT-TYPE
			SYNTAX PtpState
			MAX-ACCESS read-only
			STATUS current
			DESCRIPTION
				"Indicates the PTP state"
		::= { gps3003c04v1Entry 73 }

		-- 1.3.6.1.4.1.10106.3.101291.1.1.75
		gps3003c04v1GnssLos OBJECT-TYPE
			SYNTAX BitFail
			MAX-ACCESS read-only
			STATUS current
			DESCRIPTION
				"GNSS loss of signal. To be cleared it has to be for 30 s in in 3D-FIX or Time mode"
		::= { gps3003c04v1Entry 75 }

		-- 1.3.6.1.4.1.10106.3.101291.1.1.76
		gps3003c04v1GnssLosTrapEnable OBJECT-TYPE
			SYNTAX AlarmEnable
			MAX-ACCESS read-write
			STATUS current
			DESCRIPTION
				"GNSS loss of signal. To be cleared it has to be for 30 s in in 3D-FIX or Time mode Trap Enable"
		::= { gps3003c04v1Entry 76 }

		-- 1.3.6.1.4.1.10106.3.101291.1.1.77
		gps3003c04v1GnssPpsLos OBJECT-TYPE
			SYNTAX BitFail
			MAX-ACCESS read-only
			STATUS current
			DESCRIPTION
				"GNSS loss of PPS. It is cleared when the error of the PPS delivered by GNSS module is less than 5 ns. It is set when the delay is greater than 50 ns"
		::= { gps3003c04v1Entry 77 }

		-- 1.3.6.1.4.1.10106.3.101291.1.1.78
		gps3003c04v1GnssPpsLosTrapEnable OBJECT-TYPE
			SYNTAX AlarmEnable
			MAX-ACCESS read-write
			STATUS current
			DESCRIPTION
				"GNSS loss of PPS. It is cleared when the error of the PPS delivered by GNSS module is less than 5 ns. It is set when the delay is greater than 50 ns Trap Enable"
		::= { gps3003c04v1Entry 78 }

		-- 1.3.6.1.4.1.10106.3.101291.1.1.79
		gps3003c04v1GnssUnlock OBJECT-TYPE
			SYNTAX BitFail
			MAX-ACCESS read-only
			STATUS current
			DESCRIPTION
				"GNSS PPS unlock. It is cleared when the error of the output PPS is less than 10 ns. It is set when the error is greater than 100 ns."
		::= { gps3003c04v1Entry 79 }

		-- 1.3.6.1.4.1.10106.3.101291.1.1.80
		gps3003c04v1GnssUnlockTrapEnable OBJECT-TYPE
			SYNTAX AlarmEnable
			MAX-ACCESS read-write
			STATUS current
			DESCRIPTION
				"GNSS PPS unlock. It is cleared when the error of the output PPS is less than 10 ns. It is set when the error is greater than 100 ns. Trap Enable"
		::= { gps3003c04v1Entry 80 }

		-- 1.3.6.1.4.1.10106.3.101291.1.1.81
		gps3003c04v1GnssPpsErr OBJECT-TYPE
			SYNTAX BitFail
			MAX-ACCESS read-only
			STATUS current
			DESCRIPTION
				"GNSS pulse error. It is cleared when the error of the output PPS is less than the value specified in 'GNSS valid PPS margin'. It is set when the error is greater than this value."
		::= { gps3003c04v1Entry 81 }

		-- 1.3.6.1.4.1.10106.3.101291.1.1.82
		gps3003c04v1GnssPpsErrTrapEnable OBJECT-TYPE
			SYNTAX AlarmEnable
			MAX-ACCESS read-write
			STATUS current
			DESCRIPTION
				"GNSS pulse error. It is cleared when the error of the output PPS is less than the value specified in 'GNSS valid PPS margin'. It is set when the error is greater than this value. Trap Enable"
		::= { gps3003c04v1Entry 82 }

		-- 1.3.6.1.4.1.10106.3.101291.1.1.83
		gps3003c04v1PtpLos OBJECT-TYPE
			SYNTAX BitFail
			MAX-ACCESS read-only
			STATUS current
			DESCRIPTION
				"PTP loss of signal.It is cleared when the PTP module is in Slave or Uncalibrated mode"
		::= { gps3003c04v1Entry 83 }

		-- 1.3.6.1.4.1.10106.3.101291.1.1.84
		gps3003c04v1PtpLosTrapEnable OBJECT-TYPE
			SYNTAX AlarmEnable
			MAX-ACCESS read-write
			STATUS current
			DESCRIPTION
				"PTP loss of signal.It is cleared when the PTP module is in Slave or Uncalibrated mode Trap Enable"
		::= { gps3003c04v1Entry 84 }

		-- 1.3.6.1.4.1.10106.3.101291.1.1.85
		gps3003c04v1PtpPpsLos OBJECT-TYPE
			SYNTAX BitFail
			MAX-ACCESS read-only
			STATUS current
			DESCRIPTION
				"PTP loss of PPS. It is cleared after 30 s receiving a valid PPS from PTP module"
		::= { gps3003c04v1Entry 85 }

		-- 1.3.6.1.4.1.10106.3.101291.1.1.86
		gps3003c04v1PtpPpsLosTrapEnable OBJECT-TYPE
			SYNTAX AlarmEnable
			MAX-ACCESS read-write
			STATUS current
			DESCRIPTION
				"PTP loss of PPS. It is cleared after 30 s receiving a valid PPS from PTP module Trap Enable"
		::= { gps3003c04v1Entry 86 }

		-- 1.3.6.1.4.1.10106.3.101291.1.1.87
		gps3003c04v1PtpUnlock OBJECT-TYPE
			SYNTAX BitFail
			MAX-ACCESS read-only
			STATUS current
			DESCRIPTION
				"PTP PPS unlock. It is cleared when the error of the output PPS is less than 25 ns. It is set when the error is greater than 250 ns."
		::= { gps3003c04v1Entry 87 }

		-- 1.3.6.1.4.1.10106.3.101291.1.1.88
		gps3003c04v1PtpUnlockTrapEnable OBJECT-TYPE
			SYNTAX AlarmEnable
			MAX-ACCESS read-write
			STATUS current
			DESCRIPTION
				"PTP PPS unlock. It is cleared when the error of the output PPS is less than 25 ns. It is set when the error is greater than 250 ns. Trap Enable"
		::= { gps3003c04v1Entry 88 }

		-- 1.3.6.1.4.1.10106.3.101291.1.1.89
		gps3003c04v1PtpPpsErr OBJECT-TYPE
			SYNTAX BitFail
			MAX-ACCESS read-only
			STATUS current
			DESCRIPTION
				"PTP PPS error. It is cleared when the error of the output PPS is less than the value specified in 'PTP valid PPS margin'. It is set when the error is greater than this value."
		::= { gps3003c04v1Entry 89 }

		-- 1.3.6.1.4.1.10106.3.101291.1.1.90
		gps3003c04v1PtpPpsErrTrapEnable OBJECT-TYPE
			SYNTAX AlarmEnable
			MAX-ACCESS read-write
			STATUS current
			DESCRIPTION
				"PTP PPS error. It is cleared when the error of the output PPS is less than the value specified in 'PTP valid PPS margin'. It is set when the error is greater than this value. Trap Enable"
		::= { gps3003c04v1Entry 90 }

		-- 1.3.6.1.4.1.10106.3.101291.1.1.91
		gps3003c04v1SyncState OBJECT-TYPE
			SYNTAX Gps2SyncState
			MAX-ACCESS read-only
			STATUS current
			DESCRIPTION
				"Indicates the synchronization state"
		::= { gps3003c04v1Entry 91 }

		-- 1.3.6.1.4.1.10106.3.101291.1.1.92
		gps3003c04v1SyncStateTrapEnable OBJECT-TYPE
			SYNTAX AlarmEnable
			MAX-ACCESS read-write
			STATUS current
			DESCRIPTION
				"Indicates the synchronization state Trap Enable"
		::= { gps3003c04v1Entry 92 }

		-- 1.3.6.1.4.1.10106.3.101291.1.1.93
		gps3003c04v1ValidPps OBJECT-TYPE
			SYNTAX Bit0No1Yes
			MAX-ACCESS read-only
			STATUS current
			DESCRIPTION
				"Indicates that the internally generated PPS signal has been phase aligned with an external reference (GNSS or PTP)"
		::= { gps3003c04v1Entry 93 }

		-- 1.3.6.1.4.1.10106.3.101291.1.1.94
		gps3003c04v1ValidPpsTrapEnable OBJECT-TYPE
			SYNTAX AlarmEnable
			MAX-ACCESS read-write
			STATUS current
			DESCRIPTION
				"Indicates that the internally generated PPS signal has been phase aligned with an external reference (GNSS or PTP) Trap Enable"
		::= { gps3003c04v1Entry 94 }

		-- 1.3.6.1.4.1.10106.3.101291.1.1.95
		gps3003c04v1ModuleActive OBJECT-TYPE
			SYNTAX Bit0No1Yes
			MAX-ACCESS read-only
			STATUS current
			DESCRIPTION
				"Indicates that this module is the one that provides the reference signals"
		::= { gps3003c04v1Entry 95 }

		-- 1.3.6.1.4.1.10106.3.101291.1.1.96
		gps3003c04v1ModuleActiveTrapEnable OBJECT-TYPE
			SYNTAX AlarmEnable
			MAX-ACCESS read-write
			STATUS current
			DESCRIPTION
				"Indicates that this module is the one that provides the reference signals Trap Enable"
		::= { gps3003c04v1Entry 96 }

		-- 1.3.6.1.4.1.10106.3.101291.1.1.97
		gps3003c04v1RedSyncState OBJECT-TYPE
			SYNTAX Gps2SyncState
			MAX-ACCESS read-only
			STATUS current
			DESCRIPTION
				"Indicates the redundant module's synchronization state"
		::= { gps3003c04v1Entry 97 }

		-- 1.3.6.1.4.1.10106.3.101291.1.1.98
		gps3003c04v1RedSyncStateTrapEnable OBJECT-TYPE
			SYNTAX AlarmEnable
			MAX-ACCESS read-write
			STATUS current
			DESCRIPTION
				"Indicates the redundant module's synchronization state Trap Enable"
		::= { gps3003c04v1Entry 98 }

		-- 1.3.6.1.4.1.10106.3.101291.1.1.99
		gps3003c04v1RedModule OBJECT-TYPE
			SYNTAX Bit0No1Yes
			MAX-ACCESS read-only
			STATUS current
			DESCRIPTION
				"Indicates if the redundant module is present"
		::= { gps3003c04v1Entry 99 }

		-- 1.3.6.1.4.1.10106.3.101291.1.1.100
		gps3003c04v1RedModuleTrapEnable OBJECT-TYPE
			SYNTAX AlarmEnable
			MAX-ACCESS read-write
			STATUS current
			DESCRIPTION
				"Indicates if the redundant module is present Trap Enable"
		::= { gps3003c04v1Entry 100 }

		-- 1.3.6.1.4.1.10106.3.101291.1.1.101
		gps3003c04v1FixMode OBJECT-TYPE
			SYNTAX Gps2FixMode
			MAX-ACCESS read-only
			STATUS current
			DESCRIPTION
				"GNSS receiver module satellite tracking mode"
		::= { gps3003c04v1Entry 101 }

		-- 1.3.6.1.4.1.10106.3.101291.1.1.102
		gps3003c04v1FixModeTrapEnable OBJECT-TYPE
			SYNTAX AlarmEnable
			MAX-ACCESS read-write
			STATUS current
			DESCRIPTION
				"GNSS receiver module satellite tracking mode Trap Enable"
		::= { gps3003c04v1Entry 102 }

		-- 1.3.6.1.4.1.10106.3.101291.1.1.103
		gps3003c04v1DiffMode OBJECT-TYPE
			SYNTAX Bit0No1Yes
			MAX-ACCESS read-only
			STATUS current
			DESCRIPTION
				"GNSS receiver receives correction data and uses them to improve provided solution"
		::= { gps3003c04v1Entry 103 }

		-- 1.3.6.1.4.1.10106.3.101291.1.1.105
		gps3003c04v1NumUsedSats OBJECT-TYPE
			SYNTAX Uint8
			MAX-ACCESS read-only
			STATUS current
			DESCRIPTION
				"Number of GNSS used in current fix"
		::= { gps3003c04v1Entry 105 }

		-- 1.3.6.1.4.1.10106.3.101291.1.1.107
		gps3003c04v1CN0Max OBJECT-TYPE
			SYNTAX LevelDbHz
			MAX-ACCESS read-only
			STATUS current
			DESCRIPTION
				"Estimated carrier to noise ratio for the best satellite in tracking"
		::= { gps3003c04v1Entry 107 }

		-- 1.3.6.1.4.1.10106.3.101291.1.1.109
		gps3003c04v1PositionAcc OBJECT-TYPE
			SYNTAX AltitudeM1
			MAX-ACCESS read-only
			STATUS current
			DESCRIPTION
				"Estimated position accuracy"
		::= { gps3003c04v1Entry 109 }

		-- 1.3.6.1.4.1.10106.3.101291.1.1.111
		gps3003c04v1TimTosOffset OBJECT-TYPE
			SYNTAX TimeX1Ns
			MAX-ACCESS read-only
			STATUS current
			DESCRIPTION
				"Estimated GNSS module PPS error"
		::= { gps3003c04v1Entry 111 }

		-- 1.3.6.1.4.1.10106.3.101291.1.1.113
		gps3003c04v1SurveyTout OBJECT-TYPE
			SYNTAX TimeS2
			MAX-ACCESS read-only
			STATUS current
			DESCRIPTION
				"Time to exit Survey-in"
		::= { gps3003c04v1Entry 113 }

		-- 1.3.6.1.4.1.10106.3.101291.1.1.115
		gps3003c04v1HoldoverTime OBJECT-TYPE
			SYNTAX GpsHoldovrTime
			MAX-ACCESS read-only
			STATUS current
			DESCRIPTION
				"Holdover time"
		::= { gps3003c04v1Entry 115 }

		-- 1.3.6.1.4.1.10106.3.101291.1.1.117
		gps3003c04v1PowerStat OBJECT-TYPE
			SYNTAX Bit0Ok1Fail
			MAX-ACCESS read-only
			STATUS current
			DESCRIPTION
				"Indicates the power supply status"
		::= { gps3003c04v1Entry 117 }

		-- 1.3.6.1.4.1.10106.3.101291.1.1.118
		gps3003c04v1PowerStatTrapEnable OBJECT-TYPE
			SYNTAX AlarmEnable
			MAX-ACCESS read-write
			STATUS current
			DESCRIPTION
				"Indicates the power supply status Trap Enable"
		::= { gps3003c04v1Entry 118 }

		-- 1.3.6.1.4.1.10106.3.101291.1.1.119
		gps3003c04v1AntennaStat OBJECT-TYPE
			SYNTAX GpsAntenaStat
			MAX-ACCESS read-only
			STATUS current
			DESCRIPTION
				"Indicates the antenna connection status"
		::= { gps3003c04v1Entry 119 }

		-- 1.3.6.1.4.1.10106.3.101291.1.1.120
		gps3003c04v1AntennaStatTrapEnable OBJECT-TYPE
			SYNTAX AlarmEnable
			MAX-ACCESS read-write
			STATUS current
			DESCRIPTION
				"Indicates the antenna connection status Trap Enable"
		::= { gps3003c04v1Entry 120 }

		-- 1.3.6.1.4.1.10106.3.101291.1.1.121
		gps3003c04v1EthLink OBJECT-TYPE
			SYNTAX Bit0No1Yes
			MAX-ACCESS read-only
			STATUS current
			DESCRIPTION
				"Indicates that the Ethernet link is OK"
		::= { gps3003c04v1Entry 121 }

		-- 1.3.6.1.4.1.10106.3.101291.1.1.122
		gps3003c04v1EthLinkTrapEnable OBJECT-TYPE
			SYNTAX AlarmEnable
			MAX-ACCESS read-write
			STATUS current
			DESCRIPTION
				"Indicates that the Ethernet link is OK Trap Enable"
		::= { gps3003c04v1Entry 122 }

		-- 1.3.6.1.4.1.10106.3.101291.1.1.123
		gps3003c04v1AdjustingFreq OBJECT-TYPE
			SYNTAX Bit0No1Yes
			MAX-ACCESS read-only
			STATUS current
			DESCRIPTION
				"Indicates that the module is adjusting the frequency"
		::= { gps3003c04v1Entry 123 }

		-- 1.3.6.1.4.1.10106.3.101291.1.1.125
		gps3003c04v1OcxoWarInProg OBJECT-TYPE
			SYNTAX Bit0No1Yes
			MAX-ACCESS read-only
			STATUS current
			DESCRIPTION
				"Indicates that the OCXO warming is in progress"
		::= { gps3003c04v1Entry 125 }

		-- 1.3.6.1.4.1.10106.3.101291.1.1.127
		gps3003c04v1OnePpsStat OBJECT-TYPE
			SYNTAX Bit0Ina1Act
			MAX-ACCESS read-only
			STATUS current
			DESCRIPTION
				"Indicates that the module is delivering a valid PPS"
		::= { gps3003c04v1Entry 127 }

		-- 1.3.6.1.4.1.10106.3.101291.1.1.128
		gps3003c04v1OnePpsStatTrapEnable OBJECT-TYPE
			SYNTAX AlarmEnable
			MAX-ACCESS read-write
			STATUS current
			DESCRIPTION
				"Indicates that the module is delivering a valid PPS Trap Enable"
		::= { gps3003c04v1Entry 128 }

		-- 1.3.6.1.4.1.10106.3.101291.1.1.129
		gps3003c04v1OnePps OBJECT-TYPE
			SYNTAX BitPps
			MAX-ACCESS read-only
			STATUS current
			DESCRIPTION
				"One pulse per second signal"
		::= { gps3003c04v1Entry 129 }

		-- 1.3.6.1.4.1.10106.3.101291.1.1.131
		gps3003c04v1GnssDelay OBJECT-TYPE
			SYNTAX TimeX1p25Ns
			MAX-ACCESS read-only
			STATUS current
			DESCRIPTION
				"PPS delay relative to GNSS"
		::= { gps3003c04v1Entry 131 }

		-- 1.3.6.1.4.1.10106.3.101291.1.1.133
		gps3003c04v1PtpDelay OBJECT-TYPE
			SYNTAX TimeX1p25Ns
			MAX-ACCESS read-only
			STATUS current
			DESCRIPTION
				"PPS delay relative to PTP"
		::= { gps3003c04v1Entry 133 }

		-- 1.3.6.1.4.1.10106.3.101291.1.1.135
		gps3003c04v1SerialNo OBJECT-TYPE
			SYNTAX SerialNo
			MAX-ACCESS read-only
			STATUS current
			DESCRIPTION
				"Serial number"
		::= { gps3003c04v1Entry 135 }

		-- 1.3.6.1.4.1.10106.3.101291.1.1.137
		gps3003c04v1GnssModVer OBJECT-TYPE
			SYNTAX UbloxF9tVer
			MAX-ACCESS read-only
			STATUS current
			DESCRIPTION
				"GNSS module version"
		::= { gps3003c04v1Entry 137 }

		-- 1.3.6.1.4.1.10106.3.101291.1.1.139
		gps3003c04v1IpNtpSrv0 OBJECT-TYPE
			SYNTAX Uint8
			MAX-ACCESS read-write
			STATUS current
			DESCRIPTION
				"NTP server IP address (0)"
		::= { gps3003c04v1Entry 139 }

		-- 1.3.6.1.4.1.10106.3.101291.1.1.141
		gps3003c04v1IpNtpSrv1 OBJECT-TYPE
			SYNTAX Uint8
			MAX-ACCESS read-write
			STATUS current
			DESCRIPTION
				"NTP server IP address (1)"
		::= { gps3003c04v1Entry 141 }

		-- 1.3.6.1.4.1.10106.3.101291.1.1.143
		gps3003c04v1IpNtpSrv2 OBJECT-TYPE
			SYNTAX Uint8
			MAX-ACCESS read-write
			STATUS current
			DESCRIPTION
				"NTP server IP address (2)"
		::= { gps3003c04v1Entry 143 }

		-- 1.3.6.1.4.1.10106.3.101291.1.1.145
		gps3003c04v1IpNtpSrv3 OBJECT-TYPE
			SYNTAX Uint8
			MAX-ACCESS read-write
			STATUS current
			DESCRIPTION
				"NTP server IP address (3)"
		::= { gps3003c04v1Entry 145 }

		-- 1.3.6.1.4.1.10106.3.101291.1.1.147
		gps3003c04v1TimeDateOk OBJECT-TYPE
			SYNTAX BitFailN
			MAX-ACCESS read-only
			STATUS current
			DESCRIPTION
				"Time and date OK"
		::= { gps3003c04v1Entry 147 }

		-- 1.3.6.1.4.1.10106.3.592801
		ase2008c01v1 OBJECT IDENTIFIER ::= { albalaProducts 592801 }

		-- 1.3.6.1.4.1.10106.3.592801.1
		ase2008c01v1Table  OBJECT-TYPE
			SYNTAX SEQUENCE OF Ase2008c01v1Entry
			MAX-ACCESS not-accessible
			STATUS current
			DESCRIPTION
				"Module  ASE2008C01V1 Table"
			::= { ase2008c01v1 1 }

		-- 1.3.6.1.4.1.10106.3.592801.1.1
		ase2008c01v1Entry  OBJECT-TYPE
			SYNTAX Ase2008c01v1Entry
			MAX-ACCESS not-accessible
			STATUS current
			DESCRIPTION
				"Module ASE2008C01V1 Entry"
			INDEX { ase2008c01v1Index }
			::= { ase2008c01v1Table 1 }

			Ase2008c01v1Entry ::=
			SEQUENCE {
				ase2008c01v1Index
				ModuleIndex,
				ase2008c01v1AdcFs
				Bit0481192,
				ase2008c01v1Invert
				Bit0No1Yes,
				ase2008c01v1BitsPerSamp
				BitsPerSample,
				ase2008c01v1TsId
				Uint16,
				ase2008c01v1PrgNum
				Uint16,
				ase2008c01v1PmtPid
				Uint16,
				ase2008c01v1BasePid
				Uint1613msb,
				ase2008c01v1AudChEn1
				Bit0No1Yes,
				ase2008c01v1AudChEn1TrapEnable
				AlarmEnable,
				ase2008c01v1AudChEn2
				Bit0No1Yes,
				ase2008c01v1AudChEn2TrapEnable
				AlarmEnable,
				ase2008c01v1AudChEn3
				Bit0No1Yes,
				ase2008c01v1AudChEn3TrapEnable
				AlarmEnable,
				ase2008c01v1AudChEn4
				Bit0No1Yes,
				ase2008c01v1AudChEn4TrapEnable
				AlarmEnable,
				ase2008c01v1AudChEn5
				Bit0No1Yes,
				ase2008c01v1AudChEn5TrapEnable
				AlarmEnable,
				ase2008c01v1AudChEn6
				Bit0No1Yes,
				ase2008c01v1AudChEn6TrapEnable
				AlarmEnable,
				ase2008c01v1AudChEn7
				Bit0No1Yes,
				ase2008c01v1AudChEn7TrapEnable
				AlarmEnable,
				ase2008c01v1AudChEn8
				Bit0No1Yes,
				ase2008c01v1AudChEn8TrapEnable
				AlarmEnable,
				ase2008c01v1CoarseGain
				LevelDbX6,
				ase2008c01v1AudClip
				BitFail,
				ase2008c01v1AudClipTrapEnable
				AlarmEnable,
				ase2008c01v1SerialNo
				SerialNo
			 }

		-- 1.3.6.1.4.1.10106.3.101291.1.1.1
		ase2008c01v1Index OBJECT-TYPE
			SYNTAX ModuleIndex
			MAX-ACCESS read-only
			STATUS current
			DESCRIPTION
				"Index of ASE2008C01V1 Table"
		::= { ase2008c01v1Entry 1 }

		-- 1.3.6.1.4.1.10106.3.101291.1.1.3
		ase2008c01v1AdcFs OBJECT-TYPE
			SYNTAX Bit0481192
			MAX-ACCESS read-write
			STATUS current
			DESCRIPTION
				"Sampling frequency"
		::= { ase2008c01v1Entry 3 }

		-- 1.3.6.1.4.1.10106.3.101291.1.1.5
		ase2008c01v1Invert OBJECT-TYPE
			SYNTAX Bit0No1Yes
			MAX-ACCESS read-write
			STATUS current
			DESCRIPTION
				"Enables signal inversion"
		::= { ase2008c01v1Entry 5 }

		-- 1.3.6.1.4.1.10106.3.101291.1.1.7
		ase2008c01v1BitsPerSamp OBJECT-TYPE
			SYNTAX BitsPerSample
			MAX-ACCESS read-write
			STATUS current
			DESCRIPTION
				"Bits per audio sample"
		::= { ase2008c01v1Entry 7 }

		-- 1.3.6.1.4.1.10106.3.101291.1.1.9
		ase2008c01v1TsId OBJECT-TYPE
			SYNTAX Uint16
			MAX-ACCESS read-write
			STATUS current
			DESCRIPTION
				"Transport Stream ID"
		::= { ase2008c01v1Entry 9 }

		-- 1.3.6.1.4.1.10106.3.101291.1.1.11
		ase2008c01v1PrgNum OBJECT-TYPE
			SYNTAX Uint16
			MAX-ACCESS read-write
			STATUS current
			DESCRIPTION
				"Service ID used for transmission"
		::= { ase2008c01v1Entry 11 }

		-- 1.3.6.1.4.1.10106.3.101291.1.1.13
		ase2008c01v1PmtPid OBJECT-TYPE
			SYNTAX Uint16
			MAX-ACCESS read-write
			STATUS current
			DESCRIPTION
				"PID for the Program Map Table corresponding to Service ID"
		::= { ase2008c01v1Entry 13 }

		-- 1.3.6.1.4.1.10106.3.101291.1.1.15
		ase2008c01v1BasePid OBJECT-TYPE
			SYNTAX Uint1613msb
			MAX-ACCESS read-write
			STATUS current
			DESCRIPTION
				"Base PID for the audio Elementary Streams"
		::= { ase2008c01v1Entry 15 }

		-- 1.3.6.1.4.1.10106.3.101291.1.1.17
		ase2008c01v1AudChEn1 OBJECT-TYPE
			SYNTAX Bit0No1Yes
			MAX-ACCESS read-write
			STATUS current
			DESCRIPTION
				"Enable channel 1 Elementary Stream transmission"
		::= { ase2008c01v1Entry 17 }

		-- 1.3.6.1.4.1.10106.3.101291.1.1.18
		ase2008c01v1AudChEn1TrapEnable OBJECT-TYPE
			SYNTAX AlarmEnable
			MAX-ACCESS read-write
			STATUS current
			DESCRIPTION
				"Enable channel 1 Elementary Stream transmission Trap Enable"
		::= { ase2008c01v1Entry 18 }

		-- 1.3.6.1.4.1.10106.3.101291.1.1.19
		ase2008c01v1AudChEn2 OBJECT-TYPE
			SYNTAX Bit0No1Yes
			MAX-ACCESS read-write
			STATUS current
			DESCRIPTION
				"Enable channel 2 Elementary Stream transmission"
		::= { ase2008c01v1Entry 19 }

		-- 1.3.6.1.4.1.10106.3.101291.1.1.20
		ase2008c01v1AudChEn2TrapEnable OBJECT-TYPE
			SYNTAX AlarmEnable
			MAX-ACCESS read-write
			STATUS current
			DESCRIPTION
				"Enable channel 2 Elementary Stream transmission Trap Enable"
		::= { ase2008c01v1Entry 20 }

		-- 1.3.6.1.4.1.10106.3.101291.1.1.21
		ase2008c01v1AudChEn3 OBJECT-TYPE
			SYNTAX Bit0No1Yes
			MAX-ACCESS read-write
			STATUS current
			DESCRIPTION
				"Enable channel 3 Elementary Stream transmission"
		::= { ase2008c01v1Entry 21 }

		-- 1.3.6.1.4.1.10106.3.101291.1.1.22
		ase2008c01v1AudChEn3TrapEnable OBJECT-TYPE
			SYNTAX AlarmEnable
			MAX-ACCESS read-write
			STATUS current
			DESCRIPTION
				"Enable channel 3 Elementary Stream transmission Trap Enable"
		::= { ase2008c01v1Entry 22 }

		-- 1.3.6.1.4.1.10106.3.101291.1.1.23
		ase2008c01v1AudChEn4 OBJECT-TYPE
			SYNTAX Bit0No1Yes
			MAX-ACCESS read-write
			STATUS current
			DESCRIPTION
				"Enable channel 4 Elementary Stream transmission"
		::= { ase2008c01v1Entry 23 }

		-- 1.3.6.1.4.1.10106.3.101291.1.1.24
		ase2008c01v1AudChEn4TrapEnable OBJECT-TYPE
			SYNTAX AlarmEnable
			MAX-ACCESS read-write
			STATUS current
			DESCRIPTION
				"Enable channel 4 Elementary Stream transmission Trap Enable"
		::= { ase2008c01v1Entry 24 }

		-- 1.3.6.1.4.1.10106.3.101291.1.1.25
		ase2008c01v1AudChEn5 OBJECT-TYPE
			SYNTAX Bit0No1Yes
			MAX-ACCESS read-write
			STATUS current
			DESCRIPTION
				"Enable channel 5 Elementary Stream transmission"
		::= { ase2008c01v1Entry 25 }

		-- 1.3.6.1.4.1.10106.3.101291.1.1.26
		ase2008c01v1AudChEn5TrapEnable OBJECT-TYPE
			SYNTAX AlarmEnable
			MAX-ACCESS read-write
			STATUS current
			DESCRIPTION
				"Enable channel 5 Elementary Stream transmission Trap Enable"
		::= { ase2008c01v1Entry 26 }

		-- 1.3.6.1.4.1.10106.3.101291.1.1.27
		ase2008c01v1AudChEn6 OBJECT-TYPE
			SYNTAX Bit0No1Yes
			MAX-ACCESS read-write
			STATUS current
			DESCRIPTION
				"Enable channel 6 Elementary Stream transmission"
		::= { ase2008c01v1Entry 27 }

		-- 1.3.6.1.4.1.10106.3.101291.1.1.28
		ase2008c01v1AudChEn6TrapEnable OBJECT-TYPE
			SYNTAX AlarmEnable
			MAX-ACCESS read-write
			STATUS current
			DESCRIPTION
				"Enable channel 6 Elementary Stream transmission Trap Enable"
		::= { ase2008c01v1Entry 28 }

		-- 1.3.6.1.4.1.10106.3.101291.1.1.29
		ase2008c01v1AudChEn7 OBJECT-TYPE
			SYNTAX Bit0No1Yes
			MAX-ACCESS read-write
			STATUS current
			DESCRIPTION
				"Enable channel 7 Elementary Stream transmission"
		::= { ase2008c01v1Entry 29 }

		-- 1.3.6.1.4.1.10106.3.101291.1.1.30
		ase2008c01v1AudChEn7TrapEnable OBJECT-TYPE
			SYNTAX AlarmEnable
			MAX-ACCESS read-write
			STATUS current
			DESCRIPTION
				"Enable channel 7 Elementary Stream transmission Trap Enable"
		::= { ase2008c01v1Entry 30 }

		-- 1.3.6.1.4.1.10106.3.101291.1.1.31
		ase2008c01v1AudChEn8 OBJECT-TYPE
			SYNTAX Bit0No1Yes
			MAX-ACCESS read-write
			STATUS current
			DESCRIPTION
				"Enable channel 8 Elementary Stream transmission"
		::= { ase2008c01v1Entry 31 }

		-- 1.3.6.1.4.1.10106.3.101291.1.1.32
		ase2008c01v1AudChEn8TrapEnable OBJECT-TYPE
			SYNTAX AlarmEnable
			MAX-ACCESS read-write
			STATUS current
			DESCRIPTION
				"Enable channel 8 Elementary Stream transmission Trap Enable"
		::= { ase2008c01v1Entry 32 }

		-- 1.3.6.1.4.1.10106.3.101291.1.1.33
		ase2008c01v1CoarseGain OBJECT-TYPE
			SYNTAX LevelDbX6
			MAX-ACCESS read-write
			STATUS current
			DESCRIPTION
				"Coarse gain adjust"
		::= { ase2008c01v1Entry 33 }

		-- 1.3.6.1.4.1.10106.3.101291.1.1.35
		ase2008c01v1AudClip OBJECT-TYPE
			SYNTAX BitFail
			MAX-ACCESS read-only
			STATUS current
			DESCRIPTION
				"Indicates clipping (due to either excessive levels at the analogue input or excessive applied gain during digital processing)"
		::= { ase2008c01v1Entry 35 }

		-- 1.3.6.1.4.1.10106.3.101291.1.1.36
		ase2008c01v1AudClipTrapEnable OBJECT-TYPE
			SYNTAX AlarmEnable
			MAX-ACCESS read-write
			STATUS current
			DESCRIPTION
				"Indicates clipping (due to either excessive levels at the analogue input or excessive applied gain during digital processing) Trap Enable"
		::= { ase2008c01v1Entry 36 }

		-- 1.3.6.1.4.1.10106.3.101291.1.1.37
		ase2008c01v1SerialNo OBJECT-TYPE
			SYNTAX SerialNo
			MAX-ACCESS read-only
			STATUS current
			DESCRIPTION
				"Serial number"
		::= { ase2008c01v1Entry 37 }

		-- 1.3.6.1.4.1.10106.3.592901
		aip2000c01v1 OBJECT IDENTIFIER ::= { albalaProducts 592901 }

		-- 1.3.6.1.4.1.10106.3.592901.1
		aip2000c01v1Table  OBJECT-TYPE
			SYNTAX SEQUENCE OF Aip2000c01v1Entry
			MAX-ACCESS not-accessible
			STATUS current
			DESCRIPTION
				"Module  AIP2000C01V1 Table"
			::= { aip2000c01v1 1 }

		-- 1.3.6.1.4.1.10106.3.592901.1.1
		aip2000c01v1Entry  OBJECT-TYPE
			SYNTAX Aip2000c01v1Entry
			MAX-ACCESS not-accessible
			STATUS current
			DESCRIPTION
				"Module AIP2000C01V1 Entry"
			INDEX { aip2000c01v1Index }
			::= { aip2000c01v1Table 1 }

			Aip2000c01v1Entry ::=
			SEQUENCE {
				aip2000c01v1Index
				ModuleIndex,
				aip2000c01v1EthMode1
				EthMode2000,
				aip2000c01v1Autosync
				AutosyncControl,
				aip2000c01v1MasterSync
				AutosyncMode,
				aip2000c01v1SpeedForce1
				Bit0Ann1For,
				aip2000c01v1EthMode2
				EthMode2000,
				aip2000c01v1SpeedForce2
				Bit0Ann1For,
				aip2000c01v1EnableSdiIn
				Bit0Dis1Ena,
				aip2000c01v1FormatTx
				SdiHd3gFmt5,
				aip2000c01v1InterfaceSel
				SdiIntSel,
				aip2000c01v1SyncInterface
				SyncMode,
				aip2000c01v1TxSrPort
				Uint16,
				aip2000c01v1TtlTx
				Uint8,
				aip2000c01v1InsGr1
				Bit0No1Yes,
				aip2000c01v1InsGr2
				Bit0No1Yes,
				aip2000c01v1InsGr3
				Bit0No1Yes,
				aip2000c01v1InsGr4
				Bit0No1Yes,
				aip2000c01v1InsercionMpx
				InsercionMpx,
				aip2000c01v1EnaAud20Bit
				Bit0Yes1No,
				aip2000c01v1SwitchMode
				Hsw3SwMode,
				aip2000c01v1SourceSel0
				SourceSel0,
				aip2000c01v1SourceSel1
				SourceSel1,
				aip2000c01v1Mode192k
				Bit0481192,
				aip2000c01v1AsrcBypass0
				Bit0No1Yes,
				aip2000c01v1AsrcBypass1
				Bit0No1Yes,
				aip2000c01v1Aes67Enable
				Aes67Discovery,
				aip2000c01v1LocalIp1Add3
				Uint8,
				aip2000c01v1LocalIp1Add2
				Uint8,
				aip2000c01v1LocalIp1Add1
				Uint8,
				aip2000c01v1LocalIp1Add0
				Uint8,
				aip2000c01v1LocalIp1Msk3
				Uint8,
				aip2000c01v1LocalIp1Msk2
				Uint8,
				aip2000c01v1LocalIp1Msk1
				Uint8,
				aip2000c01v1LocalIp1Msk0
				Uint8,
				aip2000c01v1Vlan1Enable
				Bit0No1Yes,
				aip2000c01v1Vlan1Id
				Uint12,
				aip2000c01v1LocalIp2Add3
				Uint8,
				aip2000c01v1LocalIp2Add2
				Uint8,
				aip2000c01v1LocalIp2Add1
				Uint8,
				aip2000c01v1LocalIp2Add0
				Uint8,
				aip2000c01v1LocalIp2Msk3
				Uint8,
				aip2000c01v1LocalIp2Msk2
				Uint8,
				aip2000c01v1LocalIp2Msk1
				Uint8,
				aip2000c01v1LocalIp2Msk0
				Uint8,
				aip2000c01v1Vlan2Enable
				Bit0No1Yes,
				aip2000c01v1Vlan2Id
				Uint12,
				aip2000c01v1LocalIpGway3
				Uint8,
				aip2000c01v1LocalIpGway2
				Uint8,
				aip2000c01v1LocalIpGway1
				Uint8,
				aip2000c01v1LocalIpGway0
				Uint8,
				aip2000c01v1Profile
				PtpProfile,
				aip2000c01v1DomainNumber
				Uint8,
				aip2000c01v1LogAnnounceInt
				PtpInterval,
				aip2000c01v1LogSyncInt
				PtpInterval,
				aip2000c01v1LogMinDRInt
				PtpInterval,
				aip2000c01v1StreamOk1
				BitFailN,
				aip2000c01v1StreamOk1TrapEnable
				AlarmEnable,
				aip2000c01v1BufferUnderf1
				BitFail,
				aip2000c01v1BufferUnderf1TrapEnable
				AlarmEnable,
				aip2000c01v1BufferOverf1
				BitFail,
				aip2000c01v1BufferOverf1TrapEnable
				AlarmEnable,
				aip2000c01v1MalformedPck1
				BitFail,
				aip2000c01v1MalformedPck1TrapEnable
				AlarmEnable,
				aip2000c01v1Rx1PckRate
				PacketRate,
				aip2000c01v1Rx1LostIpPk
				PacketNum,
				aip2000c01v1Rx1DupIpPck
				PacketNum,
				aip2000c01v1MaxBuffLevel1
				BufferPercentag,
				aip2000c01v1MinBuffLevel1
				BufferPercentag,
				aip2000c01v1StreamOk2
				BitFailN,
				aip2000c01v1StreamOk2TrapEnable
				AlarmEnable,
				aip2000c01v1BufferUnderf2
				BitFail,
				aip2000c01v1BufferUnderf2TrapEnable
				AlarmEnable,
				aip2000c01v1BufferOverf2
				BitFail,
				aip2000c01v1BufferOverf2TrapEnable
				AlarmEnable,
				aip2000c01v1MalformedPck2
				BitFail,
				aip2000c01v1MalformedPck2TrapEnable
				AlarmEnable,
				aip2000c01v1Rx2PckRate
				PacketRate,
				aip2000c01v1Rx2LostIpPk
				PacketNum,
				aip2000c01v1Rx2DupIpPck
				PacketNum,
				aip2000c01v1MaxBuffLevel2
				BufferPercentag,
				aip2000c01v1MinBuffLevel2
				BufferPercentag,
				aip2000c01v1StreamOk3
				BitFailN,
				aip2000c01v1StreamOk3TrapEnable
				AlarmEnable,
				aip2000c01v1BufferUnderf3
				BitFail,
				aip2000c01v1BufferUnderf3TrapEnable
				AlarmEnable,
				aip2000c01v1BufferOverf3
				BitFail,
				aip2000c01v1BufferOverf3TrapEnable
				AlarmEnable,
				aip2000c01v1MalformedPck3
				BitFail,
				aip2000c01v1MalformedPck3TrapEnable
				AlarmEnable,
				aip2000c01v1Rx3PckRate
				PacketRate,
				aip2000c01v1Rx3LostIpPk
				PacketNum,
				aip2000c01v1Rx3DupIpPck
				PacketNum,
				aip2000c01v1MaxBuffLevel3
				BufferPercentag,
				aip2000c01v1MinBuffLevel3
				BufferPercentag,
				aip2000c01v1StreamOk4
				BitFailN,
				aip2000c01v1StreamOk4TrapEnable
				AlarmEnable,
				aip2000c01v1BufferUnderf4
				BitFail,
				aip2000c01v1BufferUnderf4TrapEnable
				AlarmEnable,
				aip2000c01v1BufferOverf4
				BitFail,
				aip2000c01v1BufferOverf4TrapEnable
				AlarmEnable,
				aip2000c01v1MalformedPck4
				BitFail,
				aip2000c01v1MalformedPck4TrapEnable
				AlarmEnable,
				aip2000c01v1Rx4PckRate
				PacketRate,
				aip2000c01v1Rx4LostIpPk
				PacketNum,
				aip2000c01v1Rx4DupIpPck
				PacketNum,
				aip2000c01v1MaxBuffLevel4
				BufferPercentag,
				aip2000c01v1MinBuffLevel4
				BufferPercentag,
				aip2000c01v1PtpMultAdd3
				Uint8,
				aip2000c01v1PtpMultAdd2
				Uint8,
				aip2000c01v1PtpMultAdd1
				Uint8,
				aip2000c01v1PtpMultAdd0
				Uint8,
				aip2000c01v1ShufOk
				BitFailN,
				aip2000c01v1ShufOkTrapEnable
				AlarmEnable,
				aip2000c01v1PtpIntSelected
				PtpStatus,
				aip2000c01v1Link1
				Ipa2EtherStat,
				aip2000c01v1Link1TrapEnable
				AlarmEnable,
				aip2000c01v1System1
				Ipa2EtherSys,
				aip2000c01v1System1TrapEnable
				AlarmEnable,
				aip2000c01v1Link2
				Ipa2EtherStat,
				aip2000c01v1Link2TrapEnable
				AlarmEnable,
				aip2000c01v1System2
				Ipa2EtherSys,
				aip2000c01v1System2TrapEnable
				AlarmEnable,
				aip2000c01v1NoSignal
				BitFail,
				aip2000c01v1NoSignalTrapEnable
				AlarmEnable,
				aip2000c01v1Unlock
				BitFail,
				aip2000c01v1UnlockTrapEnable
				AlarmEnable,
				aip2000c01v1EdhError
				BitFail,
				aip2000c01v1Format
				SdiHd3gFmt3,
				aip2000c01v1FormatTrapEnable
				AlarmEnable,
				aip2000c01v1PtpState
				PtpState,
				aip2000c01v1PtpStateTrapEnable
				AlarmEnable,
				aip2000c01v1TxWorkinStat1
				BitFailN,
				aip2000c01v1TxWorkinStat1TrapEnable
				AlarmEnable,
				aip2000c01v1ArpValid1
				BitFailN,
				aip2000c01v1ArpValid1TrapEnable
				AlarmEnable,
				aip2000c01v1IcmpError1
				BitFailN,
				aip2000c01v1IcmpError1TrapEnable
				AlarmEnable,
				aip2000c01v1TxWorkinStat2
				BitFailN,
				aip2000c01v1TxWorkinStat2TrapEnable
				AlarmEnable,
				aip2000c01v1ArpValid2
				BitFailN,
				aip2000c01v1ArpValid2TrapEnable
				AlarmEnable,
				aip2000c01v1IcmpError2
				BitFailN,
				aip2000c01v1IcmpError2TrapEnable
				AlarmEnable,
				aip2000c01v1TxWorkinStat3
				BitFailN,
				aip2000c01v1TxWorkinStat3TrapEnable
				AlarmEnable,
				aip2000c01v1ArpValid3
				BitFailN,
				aip2000c01v1ArpValid3TrapEnable
				AlarmEnable,
				aip2000c01v1IcmpError3
				BitFailN,
				aip2000c01v1IcmpError3TrapEnable
				AlarmEnable,
				aip2000c01v1TxWorkinStat4
				BitFailN,
				aip2000c01v1TxWorkinStat4TrapEnable
				AlarmEnable,
				aip2000c01v1ArpValid4
				BitFailN,
				aip2000c01v1ArpValid4TrapEnable
				AlarmEnable,
				aip2000c01v1IcmpError4
				BitFailN,
				aip2000c01v1IcmpError4TrapEnable
				AlarmEnable,
				aip2000c01v1AsrcUnlocked1
				BitFail,
				aip2000c01v1AsrcUnlocked1TrapEnable
				AlarmEnable,
				aip2000c01v1ProcessorStat1
				BitFail,
				aip2000c01v1ProcessorStat1TrapEnable
				AlarmEnable,
				aip2000c01v1AsrcUnlocked2
				BitFail,
				aip2000c01v1AsrcUnlocked2TrapEnable
				AlarmEnable,
				aip2000c01v1ProcessorStat2
				BitFail,
				aip2000c01v1ProcessorStat2TrapEnable
				AlarmEnable,
				aip2000c01v1Seamless0
				BitFail,
				aip2000c01v1Seamless0TrapEnable
				AlarmEnable,
				aip2000c01v1Seamless1
				BitFail,
				aip2000c01v1Seamless1TrapEnable
				AlarmEnable,
				aip2000c01v1ClkStatus
				ClkStatus,
				aip2000c01v1ClkStatusTrapEnable
				AlarmEnable,
				aip2000c01v1Grp1Pres
				BitFailN,
				aip2000c01v1Grp1PresTrapEnable
				AlarmEnable,
				aip2000c01v1PresenciaMpx
				BitFailN,
				aip2000c01v1PresenciaMpxTrapEnable
				AlarmEnable,
				aip2000c01v1Grp2Pres
				BitFailN,
				aip2000c01v1Grp2PresTrapEnable
				AlarmEnable,
				aip2000c01v1Grp3Pres
				BitFailN,
				aip2000c01v1Grp3PresTrapEnable
				AlarmEnable,
				aip2000c01v1Grp4Pres
				BitFailN,
				aip2000c01v1Grp4PresTrapEnable
				AlarmEnable,
				aip2000c01v1SerialNo
				SerialNo,
				aip2000c01v1Priority0
				SourceSel0,
				aip2000c01v1Priority1
				SourceSel1,
				aip2000c01v1RecTime
				TimeS2,
				aip2000c01v1PtpDelayAsym
				TimeX1Us,
				aip2000c01v1StatReset
				Bit0No1Yes,
				aip2000c01v1StatMode
				Bit01s1Total,
				aip2000c01v1ClockOffset
				TimeX1Us,
				aip2000c01v1ClockDelay
				TimeX1Us,
				aip2000c01v1Address12En
				Bit0No1Yes,
				aip2000c01v1Address22En
				Bit0No1Yes,
				aip2000c01v1LocalIp3Add3
				Uint8,
				aip2000c01v1LocalIp3Add2
				Uint8,
				aip2000c01v1LocalIp3Add1
				Uint8,
				aip2000c01v1LocalIp3Add0
				Uint8,
				aip2000c01v1LocalIp3Msk3
				Uint8,
				aip2000c01v1LocalIp3Msk2
				Uint8,
				aip2000c01v1LocalIp3Msk1
				Uint8,
				aip2000c01v1LocalIp3Msk0
				Uint8,
				aip2000c01v1Vlan3Enable
				Bit0No1Yes,
				aip2000c01v1Vlan3Id
				Uint12,
				aip2000c01v1LocalIp4Add3
				Uint8,
				aip2000c01v1LocalIp4Add2
				Uint8,
				aip2000c01v1LocalIp4Add1
				Uint8,
				aip2000c01v1LocalIp4Add0
				Uint8,
				aip2000c01v1LocalIp4Msk3
				Uint8,
				aip2000c01v1LocalIp4Msk2
				Uint8,
				aip2000c01v1LocalIp4Msk1
				Uint8,
				aip2000c01v1LocalIp4Msk0
				Uint8,
				aip2000c01v1Vlan4Enable
				Bit0No1Yes,
				aip2000c01v1Vlan4Id
				Uint12,
				aip2000c01v1RxFail1
				BitFail,
				aip2000c01v1RxFail2
				BitFail,
				aip2000c01v1RxFail3
				BitFail,
				aip2000c01v1RxFail4
				BitFail,
				aip2000c01v1VlanPriority1
				Uint3,
				aip2000c01v1VlanPriority2
				Uint3,
				aip2000c01v1VlanPriority3
				Uint3,
				aip2000c01v1VlanPriority4
				Uint3,
				aip2000c01v1RxTimeRst
				TimeS6
			 }

		-- 1.3.6.1.4.1.10106.3.101291.1.1.1
		aip2000c01v1Index OBJECT-TYPE
			SYNTAX ModuleIndex
			MAX-ACCESS read-only
			STATUS current
			DESCRIPTION
				"Index of AIP2000C01V1 Table"
		::= { aip2000c01v1Entry 1 }

		-- 1.3.6.1.4.1.10106.3.101291.1.1.3
		aip2000c01v1EthMode1 OBJECT-TYPE
			SYNTAX EthMode2000
			MAX-ACCESS read-write
			STATUS current
			DESCRIPTION
				"Allows selecting the Ethernet operating mode"
		::= { aip2000c01v1Entry 3 }

		-- 1.3.6.1.4.1.10106.3.101291.1.1.5
		aip2000c01v1Autosync OBJECT-TYPE
			SYNTAX AutosyncControl
			MAX-ACCESS read-write
			STATUS current
			DESCRIPTION
				"Synchronization mode"
		::= { aip2000c01v1Entry 5 }

		-- 1.3.6.1.4.1.10106.3.101291.1.1.7
		aip2000c01v1MasterSync OBJECT-TYPE
			SYNTAX AutosyncMode
			MAX-ACCESS read-write
			STATUS current
			DESCRIPTION
				"Autosync role"
		::= { aip2000c01v1Entry 7 }

		-- 1.3.6.1.4.1.10106.3.101291.1.1.9
		aip2000c01v1SpeedForce1 OBJECT-TYPE
			SYNTAX Bit0Ann1For
			MAX-ACCESS read-write
			STATUS current
			DESCRIPTION
				"Allows selecting if the speed/mode is forced or announced for autonegotiation"
		::= { aip2000c01v1Entry 9 }

		-- 1.3.6.1.4.1.10106.3.101291.1.1.11
		aip2000c01v1EthMode2 OBJECT-TYPE
			SYNTAX EthMode2000
			MAX-ACCESS read-write
			STATUS current
			DESCRIPTION
				"Allows selecting the Ethernet operating mode"
		::= { aip2000c01v1Entry 11 }

		-- 1.3.6.1.4.1.10106.3.101291.1.1.13
		aip2000c01v1SpeedForce2 OBJECT-TYPE
			SYNTAX Bit0Ann1For
			MAX-ACCESS read-write
			STATUS current
			DESCRIPTION
				"Allows selecting if the speed/mode is forced or announced for autonegotiation"
		::= { aip2000c01v1Entry 13 }

		-- 1.3.6.1.4.1.10106.3.101291.1.1.15
		aip2000c01v1EnableSdiIn OBJECT-TYPE
			SYNTAX Bit0Dis1Ena
			MAX-ACCESS read-write
			STATUS current
			DESCRIPTION
				"Enable SDI IN"
		::= { aip2000c01v1Entry 15 }

		-- 1.3.6.1.4.1.10106.3.101291.1.1.17
		aip2000c01v1FormatTx OBJECT-TYPE
			SYNTAX SdiHd3gFmt5
			MAX-ACCESS read-write
			STATUS current
			DESCRIPTION
				"SDI TX format"
		::= { aip2000c01v1Entry 17 }

		-- 1.3.6.1.4.1.10106.3.101291.1.1.19
		aip2000c01v1InterfaceSel OBJECT-TYPE
			SYNTAX SdiIntSel
			MAX-ACCESS read-write
			STATUS current
			DESCRIPTION
				"Input interface selection"
		::= { aip2000c01v1Entry 19 }

		-- 1.3.6.1.4.1.10106.3.101291.1.1.21
		aip2000c01v1SyncInterface OBJECT-TYPE
			SYNTAX SyncMode
			MAX-ACCESS read-write
			STATUS current
			DESCRIPTION
				"Syncrhonism interface"
		::= { aip2000c01v1Entry 21 }

		-- 1.3.6.1.4.1.10106.3.101291.1.1.23
		aip2000c01v1TxSrPort OBJECT-TYPE
			SYNTAX Uint16
			MAX-ACCESS read-write
			STATUS current
			DESCRIPTION
				"Default source port"
		::= { aip2000c01v1Entry 23 }

		-- 1.3.6.1.4.1.10106.3.101291.1.1.25
		aip2000c01v1TtlTx OBJECT-TYPE
			SYNTAX Uint8
			MAX-ACCESS read-write
			STATUS current
			DESCRIPTION
				"Time To Life for transmitted packets"
		::= { aip2000c01v1Entry 25 }

		-- 1.3.6.1.4.1.10106.3.101291.1.1.27
		aip2000c01v1InsGr1 OBJECT-TYPE
			SYNTAX Bit0No1Yes
			MAX-ACCESS read-write
			STATUS current
			DESCRIPTION
				"Allows selecting if all the group 1 audio packets are deleted and then embedded"
		::= { aip2000c01v1Entry 27 }

		-- 1.3.6.1.4.1.10106.3.101291.1.1.29
		aip2000c01v1InsGr2 OBJECT-TYPE
			SYNTAX Bit0No1Yes
			MAX-ACCESS read-write
			STATUS current
			DESCRIPTION
				"Allows selecting if all the group 2 audio packets are deleted and then embedded"
		::= { aip2000c01v1Entry 29 }

		-- 1.3.6.1.4.1.10106.3.101291.1.1.31
		aip2000c01v1InsGr3 OBJECT-TYPE
			SYNTAX Bit0No1Yes
			MAX-ACCESS read-write
			STATUS current
			DESCRIPTION
				"Allows selecting if all the group 3 audio packets are deleted and then embedded"
		::= { aip2000c01v1Entry 31 }

		-- 1.3.6.1.4.1.10106.3.101291.1.1.33
		aip2000c01v1InsGr4 OBJECT-TYPE
			SYNTAX Bit0No1Yes
			MAX-ACCESS read-write
			STATUS current
			DESCRIPTION
				"Allows selecting if all the group 4 audio packets are deleted and then embedded"
		::= { aip2000c01v1Entry 33 }

		-- 1.3.6.1.4.1.10106.3.101291.1.1.35
		aip2000c01v1InsercionMpx OBJECT-TYPE
			SYNTAX InsercionMpx
			MAX-ACCESS read-write
			STATUS current
			DESCRIPTION
				"MPX insertion: channels 1-8 (Audio can only be inserted in channels 1 to 3)"
		::= { aip2000c01v1Entry 35 }

		-- 1.3.6.1.4.1.10106.3.101291.1.1.37
		aip2000c01v1EnaAud20Bit OBJECT-TYPE
			SYNTAX Bit0Yes1No
			MAX-ACCESS read-write
			STATUS current
			DESCRIPTION
				"Allows embedding 24-bit audio in SD signals"
		::= { aip2000c01v1Entry 37 }

		-- 1.3.6.1.4.1.10106.3.101291.1.1.39
		aip2000c01v1SwitchMode OBJECT-TYPE
			SYNTAX Hsw3SwMode
			MAX-ACCESS read-write
			STATUS current
			DESCRIPTION
				"Swtch mode"
		::= { aip2000c01v1Entry 39 }

		-- 1.3.6.1.4.1.10106.3.101291.1.1.41
		aip2000c01v1SourceSel0 OBJECT-TYPE
			SYNTAX SourceSel0
			MAX-ACCESS read-write
			STATUS current
			DESCRIPTION
				"Selected source RX1/RX2"
		::= { aip2000c01v1Entry 41 }

		-- 1.3.6.1.4.1.10106.3.101291.1.1.43
		aip2000c01v1SourceSel1 OBJECT-TYPE
			SYNTAX SourceSel1
			MAX-ACCESS read-write
			STATUS current
			DESCRIPTION
				"Selected source RX3/RX4"
		::= { aip2000c01v1Entry 43 }

		-- 1.3.6.1.4.1.10106.3.101291.1.1.45
		aip2000c01v1Mode192k OBJECT-TYPE
			SYNTAX Bit0481192
			MAX-ACCESS read-write
			STATUS current
			DESCRIPTION
				"Sampling frequency"
		::= { aip2000c01v1Entry 45 }

		-- 1.3.6.1.4.1.10106.3.101291.1.1.47
		aip2000c01v1AsrcBypass0 OBJECT-TYPE
			SYNTAX Bit0No1Yes
			MAX-ACCESS read-write
			STATUS current
			DESCRIPTION
				"ASRC bypass enable"
		::= { aip2000c01v1Entry 47 }

		-- 1.3.6.1.4.1.10106.3.101291.1.1.49
		aip2000c01v1AsrcBypass1 OBJECT-TYPE
			SYNTAX Bit0No1Yes
			MAX-ACCESS read-write
			STATUS current
			DESCRIPTION
				"ASRC bypass enable"
		::= { aip2000c01v1Entry 49 }

		-- 1.3.6.1.4.1.10106.3.101291.1.1.51
		aip2000c01v1Aes67Enable OBJECT-TYPE
			SYNTAX Aes67Discovery
			MAX-ACCESS read-write
			STATUS current
			DESCRIPTION
				"AES67 protocol"
		::= { aip2000c01v1Entry 51 }

		-- 1.3.6.1.4.1.10106.3.101291.1.1.53
		aip2000c01v1LocalIp1Add3 OBJECT-TYPE
			SYNTAX Uint8
			MAX-ACCESS read-write
			STATUS current
			DESCRIPTION
				"IP address (3)"
		::= { aip2000c01v1Entry 53 }

		-- 1.3.6.1.4.1.10106.3.101291.1.1.55
		aip2000c01v1LocalIp1Add2 OBJECT-TYPE
			SYNTAX Uint8
			MAX-ACCESS read-write
			STATUS current
			DESCRIPTION
				"IP address (2)"
		::= { aip2000c01v1Entry 55 }

		-- 1.3.6.1.4.1.10106.3.101291.1.1.57
		aip2000c01v1LocalIp1Add1 OBJECT-TYPE
			SYNTAX Uint8
			MAX-ACCESS read-write
			STATUS current
			DESCRIPTION
				"IP address (1)"
		::= { aip2000c01v1Entry 57 }

		-- 1.3.6.1.4.1.10106.3.101291.1.1.59
		aip2000c01v1LocalIp1Add0 OBJECT-TYPE
			SYNTAX Uint8
			MAX-ACCESS read-write
			STATUS current
			DESCRIPTION
				"IP address (0)"
		::= { aip2000c01v1Entry 59 }

		-- 1.3.6.1.4.1.10106.3.101291.1.1.61
		aip2000c01v1LocalIp1Msk3 OBJECT-TYPE
			SYNTAX Uint8
			MAX-ACCESS read-write
			STATUS current
			DESCRIPTION
				"IP mask (3)"
		::= { aip2000c01v1Entry 61 }

		-- 1.3.6.1.4.1.10106.3.101291.1.1.63
		aip2000c01v1LocalIp1Msk2 OBJECT-TYPE
			SYNTAX Uint8
			MAX-ACCESS read-write
			STATUS current
			DESCRIPTION
				"IP mask (2)"
		::= { aip2000c01v1Entry 63 }

		-- 1.3.6.1.4.1.10106.3.101291.1.1.65
		aip2000c01v1LocalIp1Msk1 OBJECT-TYPE
			SYNTAX Uint8
			MAX-ACCESS read-write
			STATUS current
			DESCRIPTION
				"IP mask (1)"
		::= { aip2000c01v1Entry 65 }

		-- 1.3.6.1.4.1.10106.3.101291.1.1.67
		aip2000c01v1LocalIp1Msk0 OBJECT-TYPE
			SYNTAX Uint8
			MAX-ACCESS read-write
			STATUS current
			DESCRIPTION
				"IP mask (0)"
		::= { aip2000c01v1Entry 67 }

		-- 1.3.6.1.4.1.10106.3.101291.1.1.69
		aip2000c01v1Vlan1Enable OBJECT-TYPE
			SYNTAX Bit0No1Yes
			MAX-ACCESS read-write
			STATUS current
			DESCRIPTION
				"VLAN Enable"
		::= { aip2000c01v1Entry 69 }

		-- 1.3.6.1.4.1.10106.3.101291.1.1.71
		aip2000c01v1Vlan1Id OBJECT-TYPE
			SYNTAX Uint12
			MAX-ACCESS read-write
			STATUS current
			DESCRIPTION
				"VLAN ID"
		::= { aip2000c01v1Entry 71 }

		-- 1.3.6.1.4.1.10106.3.101291.1.1.73
		aip2000c01v1LocalIp2Add3 OBJECT-TYPE
			SYNTAX Uint8
			MAX-ACCESS read-write
			STATUS current
			DESCRIPTION
				"IP address (3)"
		::= { aip2000c01v1Entry 73 }

		-- 1.3.6.1.4.1.10106.3.101291.1.1.75
		aip2000c01v1LocalIp2Add2 OBJECT-TYPE
			SYNTAX Uint8
			MAX-ACCESS read-write
			STATUS current
			DESCRIPTION
				"IP address (2)"
		::= { aip2000c01v1Entry 75 }

		-- 1.3.6.1.4.1.10106.3.101291.1.1.77
		aip2000c01v1LocalIp2Add1 OBJECT-TYPE
			SYNTAX Uint8
			MAX-ACCESS read-write
			STATUS current
			DESCRIPTION
				"IP address (1)"
		::= { aip2000c01v1Entry 77 }

		-- 1.3.6.1.4.1.10106.3.101291.1.1.79
		aip2000c01v1LocalIp2Add0 OBJECT-TYPE
			SYNTAX Uint8
			MAX-ACCESS read-write
			STATUS current
			DESCRIPTION
				"IP address (0)"
		::= { aip2000c01v1Entry 79 }

		-- 1.3.6.1.4.1.10106.3.101291.1.1.81
		aip2000c01v1LocalIp2Msk3 OBJECT-TYPE
			SYNTAX Uint8
			MAX-ACCESS read-write
			STATUS current
			DESCRIPTION
				"IP mask (3)"
		::= { aip2000c01v1Entry 81 }

		-- 1.3.6.1.4.1.10106.3.101291.1.1.83
		aip2000c01v1LocalIp2Msk2 OBJECT-TYPE
			SYNTAX Uint8
			MAX-ACCESS read-write
			STATUS current
			DESCRIPTION
				"IP mask (2)"
		::= { aip2000c01v1Entry 83 }

		-- 1.3.6.1.4.1.10106.3.101291.1.1.85
		aip2000c01v1LocalIp2Msk1 OBJECT-TYPE
			SYNTAX Uint8
			MAX-ACCESS read-write
			STATUS current
			DESCRIPTION
				"IP mask (1)"
		::= { aip2000c01v1Entry 85 }

		-- 1.3.6.1.4.1.10106.3.101291.1.1.87
		aip2000c01v1LocalIp2Msk0 OBJECT-TYPE
			SYNTAX Uint8
			MAX-ACCESS read-write
			STATUS current
			DESCRIPTION
				"IP mask (0)"
		::= { aip2000c01v1Entry 87 }

		-- 1.3.6.1.4.1.10106.3.101291.1.1.89
		aip2000c01v1Vlan2Enable OBJECT-TYPE
			SYNTAX Bit0No1Yes
			MAX-ACCESS read-write
			STATUS current
			DESCRIPTION
				"VLAN Enable"
		::= { aip2000c01v1Entry 89 }

		-- 1.3.6.1.4.1.10106.3.101291.1.1.91
		aip2000c01v1Vlan2Id OBJECT-TYPE
			SYNTAX Uint12
			MAX-ACCESS read-write
			STATUS current
			DESCRIPTION
				"VLAN ID"
		::= { aip2000c01v1Entry 91 }

		-- 1.3.6.1.4.1.10106.3.101291.1.1.93
		aip2000c01v1LocalIpGway3 OBJECT-TYPE
			SYNTAX Uint8
			MAX-ACCESS read-write
			STATUS current
			DESCRIPTION
				"Gateway IP address (3)"
		::= { aip2000c01v1Entry 93 }

		-- 1.3.6.1.4.1.10106.3.101291.1.1.95
		aip2000c01v1LocalIpGway2 OBJECT-TYPE
			SYNTAX Uint8
			MAX-ACCESS read-write
			STATUS current
			DESCRIPTION
				"Gateway IP address (2)"
		::= { aip2000c01v1Entry 95 }

		-- 1.3.6.1.4.1.10106.3.101291.1.1.97
		aip2000c01v1LocalIpGway1 OBJECT-TYPE
			SYNTAX Uint8
			MAX-ACCESS read-write
			STATUS current
			DESCRIPTION
				"Gateway IP address (1)"
		::= { aip2000c01v1Entry 97 }

		-- 1.3.6.1.4.1.10106.3.101291.1.1.99
		aip2000c01v1LocalIpGway0 OBJECT-TYPE
			SYNTAX Uint8
			MAX-ACCESS read-write
			STATUS current
			DESCRIPTION
				"Gateway IP address (0)"
		::= { aip2000c01v1Entry 99 }

		-- 1.3.6.1.4.1.10106.3.101291.1.1.101
		aip2000c01v1Profile OBJECT-TYPE
			SYNTAX PtpProfile
			MAX-ACCESS read-write
			STATUS current
			DESCRIPTION
				"Allows loading default values of a PTP profile"
		::= { aip2000c01v1Entry 101 }

		-- 1.3.6.1.4.1.10106.3.101291.1.1.103
		aip2000c01v1DomainNumber OBJECT-TYPE
			SYNTAX Uint8
			MAX-ACCESS read-write
			STATUS current
			DESCRIPTION
				"Allows selecting the Domanin number attribute of the local clock"
		::= { aip2000c01v1Entry 103 }

		-- 1.3.6.1.4.1.10106.3.101291.1.1.105
		aip2000c01v1LogAnnounceInt OBJECT-TYPE
			SYNTAX PtpInterval
			MAX-ACCESS read-write
			STATUS current
			DESCRIPTION
				"Allows selecting the mean interval between Announce messages"
		::= { aip2000c01v1Entry 105 }

		-- 1.3.6.1.4.1.10106.3.101291.1.1.107
		aip2000c01v1LogSyncInt OBJECT-TYPE
			SYNTAX PtpInterval
			MAX-ACCESS read-write
			STATUS current
			DESCRIPTION
				"Allows selecting the mean interval between Sync messages"
		::= { aip2000c01v1Entry 107 }

		-- 1.3.6.1.4.1.10106.3.101291.1.1.109
		aip2000c01v1LogMinDRInt OBJECT-TYPE
			SYNTAX PtpInterval
			MAX-ACCESS read-write
			STATUS current
			DESCRIPTION
				"Allows selecting the minimum mean interval between Delay_Req messages"
		::= { aip2000c01v1Entry 109 }

		-- 1.3.6.1.4.1.10106.3.101291.1.1.111
		aip2000c01v1StreamOk1 OBJECT-TYPE
			SYNTAX BitFailN
			MAX-ACCESS read-only
			STATUS current
			DESCRIPTION
				"AES67 RX1 stream received"
		::= { aip2000c01v1Entry 111 }

		-- 1.3.6.1.4.1.10106.3.101291.1.1.112
		aip2000c01v1StreamOk1TrapEnable OBJECT-TYPE
			SYNTAX AlarmEnable
			MAX-ACCESS read-write
			STATUS current
			DESCRIPTION
				"AES67 RX1 stream received Trap Enable"
		::= { aip2000c01v1Entry 112 }

		-- 1.3.6.1.4.1.10106.3.101291.1.1.113
		aip2000c01v1BufferUnderf1 OBJECT-TYPE
			SYNTAX BitFail
			MAX-ACCESS read-only
			STATUS current
			DESCRIPTION
				"Buffer underflow"
		::= { aip2000c01v1Entry 113 }

		-- 1.3.6.1.4.1.10106.3.101291.1.1.114
		aip2000c01v1BufferUnderf1TrapEnable OBJECT-TYPE
			SYNTAX AlarmEnable
			MAX-ACCESS read-write
			STATUS current
			DESCRIPTION
				"Buffer underflow Trap Enable"
		::= { aip2000c01v1Entry 114 }

		-- 1.3.6.1.4.1.10106.3.101291.1.1.115
		aip2000c01v1BufferOverf1 OBJECT-TYPE
			SYNTAX BitFail
			MAX-ACCESS read-only
			STATUS current
			DESCRIPTION
				"Buffer_overflow/TS error"
		::= { aip2000c01v1Entry 115 }

		-- 1.3.6.1.4.1.10106.3.101291.1.1.116
		aip2000c01v1BufferOverf1TrapEnable OBJECT-TYPE
			SYNTAX AlarmEnable
			MAX-ACCESS read-write
			STATUS current
			DESCRIPTION
				"Buffer_overflow/TS error Trap Enable"
		::= { aip2000c01v1Entry 116 }

		-- 1.3.6.1.4.1.10106.3.101291.1.1.117
		aip2000c01v1MalformedPck1 OBJECT-TYPE
			SYNTAX BitFail
			MAX-ACCESS read-only
			STATUS current
			DESCRIPTION
				"Malformed packets"
		::= { aip2000c01v1Entry 117 }

		-- 1.3.6.1.4.1.10106.3.101291.1.1.118
		aip2000c01v1MalformedPck1TrapEnable OBJECT-TYPE
			SYNTAX AlarmEnable
			MAX-ACCESS read-write
			STATUS current
			DESCRIPTION
				"Malformed packets Trap Enable"
		::= { aip2000c01v1Entry 118 }

		-- 1.3.6.1.4.1.10106.3.101291.1.1.119
		aip2000c01v1Rx1PckRate OBJECT-TYPE
			SYNTAX PacketRate
			MAX-ACCESS read-only
			STATUS current
			DESCRIPTION
				"IP packet rate"
		::= { aip2000c01v1Entry 119 }

		-- 1.3.6.1.4.1.10106.3.101291.1.1.121
		aip2000c01v1Rx1LostIpPk OBJECT-TYPE
			SYNTAX PacketNum
			MAX-ACCESS read-only
			STATUS current
			DESCRIPTION
				"Lost IP packets rate"
		::= { aip2000c01v1Entry 121 }

		-- 1.3.6.1.4.1.10106.3.101291.1.1.123
		aip2000c01v1Rx1DupIpPck OBJECT-TYPE
			SYNTAX PacketNum
			MAX-ACCESS read-only
			STATUS current
			DESCRIPTION
				"Duplicated IP packets rate"
		::= { aip2000c01v1Entry 123 }

		-- 1.3.6.1.4.1.10106.3.101291.1.1.125
		aip2000c01v1MaxBuffLevel1 OBJECT-TYPE
			SYNTAX BufferPercentag
			MAX-ACCESS read-only
			STATUS current
			DESCRIPTION
				"Maximum buffer level"
		::= { aip2000c01v1Entry 125 }

		-- 1.3.6.1.4.1.10106.3.101291.1.1.127
		aip2000c01v1MinBuffLevel1 OBJECT-TYPE
			SYNTAX BufferPercentag
			MAX-ACCESS read-only
			STATUS current
			DESCRIPTION
				"Minimum buffer level"
		::= { aip2000c01v1Entry 127 }

		-- 1.3.6.1.4.1.10106.3.101291.1.1.129
		aip2000c01v1StreamOk2 OBJECT-TYPE
			SYNTAX BitFailN
			MAX-ACCESS read-only
			STATUS current
			DESCRIPTION
				"AES67 RX2 stream received"
		::= { aip2000c01v1Entry 129 }

		-- 1.3.6.1.4.1.10106.3.101291.1.1.130
		aip2000c01v1StreamOk2TrapEnable OBJECT-TYPE
			SYNTAX AlarmEnable
			MAX-ACCESS read-write
			STATUS current
			DESCRIPTION
				"AES67 RX2 stream received Trap Enable"
		::= { aip2000c01v1Entry 130 }

		-- 1.3.6.1.4.1.10106.3.101291.1.1.131
		aip2000c01v1BufferUnderf2 OBJECT-TYPE
			SYNTAX BitFail
			MAX-ACCESS read-only
			STATUS current
			DESCRIPTION
				"Buffer underflow"
		::= { aip2000c01v1Entry 131 }

		-- 1.3.6.1.4.1.10106.3.101291.1.1.132
		aip2000c01v1BufferUnderf2TrapEnable OBJECT-TYPE
			SYNTAX AlarmEnable
			MAX-ACCESS read-write
			STATUS current
			DESCRIPTION
				"Buffer underflow Trap Enable"
		::= { aip2000c01v1Entry 132 }

		-- 1.3.6.1.4.1.10106.3.101291.1.1.133
		aip2000c01v1BufferOverf2 OBJECT-TYPE
			SYNTAX BitFail
			MAX-ACCESS read-only
			STATUS current
			DESCRIPTION
				"Buffer_overflow/TS error"
		::= { aip2000c01v1Entry 133 }

		-- 1.3.6.1.4.1.10106.3.101291.1.1.134
		aip2000c01v1BufferOverf2TrapEnable OBJECT-TYPE
			SYNTAX AlarmEnable
			MAX-ACCESS read-write
			STATUS current
			DESCRIPTION
				"Buffer_overflow/TS error Trap Enable"
		::= { aip2000c01v1Entry 134 }

		-- 1.3.6.1.4.1.10106.3.101291.1.1.135
		aip2000c01v1MalformedPck2 OBJECT-TYPE
			SYNTAX BitFail
			MAX-ACCESS read-only
			STATUS current
			DESCRIPTION
				"Malformed packets"
		::= { aip2000c01v1Entry 135 }

		-- 1.3.6.1.4.1.10106.3.101291.1.1.136
		aip2000c01v1MalformedPck2TrapEnable OBJECT-TYPE
			SYNTAX AlarmEnable
			MAX-ACCESS read-write
			STATUS current
			DESCRIPTION
				"Malformed packets Trap Enable"
		::= { aip2000c01v1Entry 136 }

		-- 1.3.6.1.4.1.10106.3.101291.1.1.137
		aip2000c01v1Rx2PckRate OBJECT-TYPE
			SYNTAX PacketRate
			MAX-ACCESS read-only
			STATUS current
			DESCRIPTION
				"IP packet rate"
		::= { aip2000c01v1Entry 137 }

		-- 1.3.6.1.4.1.10106.3.101291.1.1.139
		aip2000c01v1Rx2LostIpPk OBJECT-TYPE
			SYNTAX PacketNum
			MAX-ACCESS read-only
			STATUS current
			DESCRIPTION
				"Lost IP packets rate"
		::= { aip2000c01v1Entry 139 }

		-- 1.3.6.1.4.1.10106.3.101291.1.1.141
		aip2000c01v1Rx2DupIpPck OBJECT-TYPE
			SYNTAX PacketNum
			MAX-ACCESS read-only
			STATUS current
			DESCRIPTION
				"Duplicated IP packets rate"
		::= { aip2000c01v1Entry 141 }

		-- 1.3.6.1.4.1.10106.3.101291.1.1.143
		aip2000c01v1MaxBuffLevel2 OBJECT-TYPE
			SYNTAX BufferPercentag
			MAX-ACCESS read-only
			STATUS current
			DESCRIPTION
				"Maximum buffer level"
		::= { aip2000c01v1Entry 143 }

		-- 1.3.6.1.4.1.10106.3.101291.1.1.145
		aip2000c01v1MinBuffLevel2 OBJECT-TYPE
			SYNTAX BufferPercentag
			MAX-ACCESS read-only
			STATUS current
			DESCRIPTION
				"Minimum buffer level"
		::= { aip2000c01v1Entry 145 }

		-- 1.3.6.1.4.1.10106.3.101291.1.1.147
		aip2000c01v1StreamOk3 OBJECT-TYPE
			SYNTAX BitFailN
			MAX-ACCESS read-only
			STATUS current
			DESCRIPTION
				"AES67 RX3 stream received"
		::= { aip2000c01v1Entry 147 }

		-- 1.3.6.1.4.1.10106.3.101291.1.1.148
		aip2000c01v1StreamOk3TrapEnable OBJECT-TYPE
			SYNTAX AlarmEnable
			MAX-ACCESS read-write
			STATUS current
			DESCRIPTION
				"AES67 RX3 stream received Trap Enable"
		::= { aip2000c01v1Entry 148 }

		-- 1.3.6.1.4.1.10106.3.101291.1.1.149
		aip2000c01v1BufferUnderf3 OBJECT-TYPE
			SYNTAX BitFail
			MAX-ACCESS read-only
			STATUS current
			DESCRIPTION
				"Buffer underflow"
		::= { aip2000c01v1Entry 149 }

		-- 1.3.6.1.4.1.10106.3.101291.1.1.150
		aip2000c01v1BufferUnderf3TrapEnable OBJECT-TYPE
			SYNTAX AlarmEnable
			MAX-ACCESS read-write
			STATUS current
			DESCRIPTION
				"Buffer underflow Trap Enable"
		::= { aip2000c01v1Entry 150 }

		-- 1.3.6.1.4.1.10106.3.101291.1.1.151
		aip2000c01v1BufferOverf3 OBJECT-TYPE
			SYNTAX BitFail
			MAX-ACCESS read-only
			STATUS current
			DESCRIPTION
				"Buffer_overflow/TS error"
		::= { aip2000c01v1Entry 151 }

		-- 1.3.6.1.4.1.10106.3.101291.1.1.152
		aip2000c01v1BufferOverf3TrapEnable OBJECT-TYPE
			SYNTAX AlarmEnable
			MAX-ACCESS read-write
			STATUS current
			DESCRIPTION
				"Buffer_overflow/TS error Trap Enable"
		::= { aip2000c01v1Entry 152 }

		-- 1.3.6.1.4.1.10106.3.101291.1.1.153
		aip2000c01v1MalformedPck3 OBJECT-TYPE
			SYNTAX BitFail
			MAX-ACCESS read-only
			STATUS current
			DESCRIPTION
				"Malformed packets"
		::= { aip2000c01v1Entry 153 }

		-- 1.3.6.1.4.1.10106.3.101291.1.1.154
		aip2000c01v1MalformedPck3TrapEnable OBJECT-TYPE
			SYNTAX AlarmEnable
			MAX-ACCESS read-write
			STATUS current
			DESCRIPTION
				"Malformed packets Trap Enable"
		::= { aip2000c01v1Entry 154 }

		-- 1.3.6.1.4.1.10106.3.101291.1.1.155
		aip2000c01v1Rx3PckRate OBJECT-TYPE
			SYNTAX PacketRate
			MAX-ACCESS read-only
			STATUS current
			DESCRIPTION
				"IP packet rate"
		::= { aip2000c01v1Entry 155 }

		-- 1.3.6.1.4.1.10106.3.101291.1.1.157
		aip2000c01v1Rx3LostIpPk OBJECT-TYPE
			SYNTAX PacketNum
			MAX-ACCESS read-only
			STATUS current
			DESCRIPTION
				"Lost IP packets rate"
		::= { aip2000c01v1Entry 157 }

		-- 1.3.6.1.4.1.10106.3.101291.1.1.159
		aip2000c01v1Rx3DupIpPck OBJECT-TYPE
			SYNTAX PacketNum
			MAX-ACCESS read-only
			STATUS current
			DESCRIPTION
				"Duplicated IP packets rate"
		::= { aip2000c01v1Entry 159 }

		-- 1.3.6.1.4.1.10106.3.101291.1.1.161
		aip2000c01v1MaxBuffLevel3 OBJECT-TYPE
			SYNTAX BufferPercentag
			MAX-ACCESS read-only
			STATUS current
			DESCRIPTION
				"Maximum buffer level"
		::= { aip2000c01v1Entry 161 }

		-- 1.3.6.1.4.1.10106.3.101291.1.1.163
		aip2000c01v1MinBuffLevel3 OBJECT-TYPE
			SYNTAX BufferPercentag
			MAX-ACCESS read-only
			STATUS current
			DESCRIPTION
				"Minimum buffer level"
		::= { aip2000c01v1Entry 163 }

		-- 1.3.6.1.4.1.10106.3.101291.1.1.165
		aip2000c01v1StreamOk4 OBJECT-TYPE
			SYNTAX BitFailN
			MAX-ACCESS read-only
			STATUS current
			DESCRIPTION
				"AES67 RX4 stream received"
		::= { aip2000c01v1Entry 165 }

		-- 1.3.6.1.4.1.10106.3.101291.1.1.166
		aip2000c01v1StreamOk4TrapEnable OBJECT-TYPE
			SYNTAX AlarmEnable
			MAX-ACCESS read-write
			STATUS current
			DESCRIPTION
				"AES67 RX4 stream received Trap Enable"
		::= { aip2000c01v1Entry 166 }

		-- 1.3.6.1.4.1.10106.3.101291.1.1.167
		aip2000c01v1BufferUnderf4 OBJECT-TYPE
			SYNTAX BitFail
			MAX-ACCESS read-only
			STATUS current
			DESCRIPTION
				"Buffer underflow"
		::= { aip2000c01v1Entry 167 }

		-- 1.3.6.1.4.1.10106.3.101291.1.1.168
		aip2000c01v1BufferUnderf4TrapEnable OBJECT-TYPE
			SYNTAX AlarmEnable
			MAX-ACCESS read-write
			STATUS current
			DESCRIPTION
				"Buffer underflow Trap Enable"
		::= { aip2000c01v1Entry 168 }

		-- 1.3.6.1.4.1.10106.3.101291.1.1.169
		aip2000c01v1BufferOverf4 OBJECT-TYPE
			SYNTAX BitFail
			MAX-ACCESS read-only
			STATUS current
			DESCRIPTION
				"Buffer_overflow/TS error"
		::= { aip2000c01v1Entry 169 }

		-- 1.3.6.1.4.1.10106.3.101291.1.1.170
		aip2000c01v1BufferOverf4TrapEnable OBJECT-TYPE
			SYNTAX AlarmEnable
			MAX-ACCESS read-write
			STATUS current
			DESCRIPTION
				"Buffer_overflow/TS error Trap Enable"
		::= { aip2000c01v1Entry 170 }

		-- 1.3.6.1.4.1.10106.3.101291.1.1.171
		aip2000c01v1MalformedPck4 OBJECT-TYPE
			SYNTAX BitFail
			MAX-ACCESS read-only
			STATUS current
			DESCRIPTION
				"Malformed packets"
		::= { aip2000c01v1Entry 171 }

		-- 1.3.6.1.4.1.10106.3.101291.1.1.172
		aip2000c01v1MalformedPck4TrapEnable OBJECT-TYPE
			SYNTAX AlarmEnable
			MAX-ACCESS read-write
			STATUS current
			DESCRIPTION
				"Malformed packets Trap Enable"
		::= { aip2000c01v1Entry 172 }

		-- 1.3.6.1.4.1.10106.3.101291.1.1.173
		aip2000c01v1Rx4PckRate OBJECT-TYPE
			SYNTAX PacketRate
			MAX-ACCESS read-only
			STATUS current
			DESCRIPTION
				"IP packet rate"
		::= { aip2000c01v1Entry 173 }

		-- 1.3.6.1.4.1.10106.3.101291.1.1.175
		aip2000c01v1Rx4LostIpPk OBJECT-TYPE
			SYNTAX PacketNum
			MAX-ACCESS read-only
			STATUS current
			DESCRIPTION
				"Lost IP packets rate"
		::= { aip2000c01v1Entry 175 }

		-- 1.3.6.1.4.1.10106.3.101291.1.1.177
		aip2000c01v1Rx4DupIpPck OBJECT-TYPE
			SYNTAX PacketNum
			MAX-ACCESS read-only
			STATUS current
			DESCRIPTION
				"Duplicated IP packets rate"
		::= { aip2000c01v1Entry 177 }

		-- 1.3.6.1.4.1.10106.3.101291.1.1.179
		aip2000c01v1MaxBuffLevel4 OBJECT-TYPE
			SYNTAX BufferPercentag
			MAX-ACCESS read-only
			STATUS current
			DESCRIPTION
				"Maximum buffer level"
		::= { aip2000c01v1Entry 179 }

		-- 1.3.6.1.4.1.10106.3.101291.1.1.181
		aip2000c01v1MinBuffLevel4 OBJECT-TYPE
			SYNTAX BufferPercentag
			MAX-ACCESS read-only
			STATUS current
			DESCRIPTION
				"Minimum buffer level"
		::= { aip2000c01v1Entry 181 }

		-- 1.3.6.1.4.1.10106.3.101291.1.1.183
		aip2000c01v1PtpMultAdd3 OBJECT-TYPE
			SYNTAX Uint8
			MAX-ACCESS read-write
			STATUS current
			DESCRIPTION
				"Autosync multicast IP address(3)"
		::= { aip2000c01v1Entry 183 }

		-- 1.3.6.1.4.1.10106.3.101291.1.1.185
		aip2000c01v1PtpMultAdd2 OBJECT-TYPE
			SYNTAX Uint8
			MAX-ACCESS read-write
			STATUS current
			DESCRIPTION
				"Autosync multicast IP address(2)"
		::= { aip2000c01v1Entry 185 }

		-- 1.3.6.1.4.1.10106.3.101291.1.1.187
		aip2000c01v1PtpMultAdd1 OBJECT-TYPE
			SYNTAX Uint8
			MAX-ACCESS read-write
			STATUS current
			DESCRIPTION
				"Autosync multicast IP address(1)"
		::= { aip2000c01v1Entry 187 }

		-- 1.3.6.1.4.1.10106.3.101291.1.1.189
		aip2000c01v1PtpMultAdd0 OBJECT-TYPE
			SYNTAX Uint8
			MAX-ACCESS read-write
			STATUS current
			DESCRIPTION
				"Autosync multicast IP address(0)"
		::= { aip2000c01v1Entry 189 }

		-- 1.3.6.1.4.1.10106.3.101291.1.1.191
		aip2000c01v1ShufOk OBJECT-TYPE
			SYNTAX BitFailN
			MAX-ACCESS read-only
			STATUS current
			DESCRIPTION
				"Shuffling ok"
		::= { aip2000c01v1Entry 191 }

		-- 1.3.6.1.4.1.10106.3.101291.1.1.192
		aip2000c01v1ShufOkTrapEnable OBJECT-TYPE
			SYNTAX AlarmEnable
			MAX-ACCESS read-write
			STATUS current
			DESCRIPTION
				"Shuffling ok Trap Enable"
		::= { aip2000c01v1Entry 192 }

		-- 1.3.6.1.4.1.10106.3.101291.1.1.193
		aip2000c01v1PtpIntSelected OBJECT-TYPE
			SYNTAX PtpStatus
			MAX-ACCESS read-only
			STATUS current
			DESCRIPTION
				"PTP interface selected"
		::= { aip2000c01v1Entry 193 }

		-- 1.3.6.1.4.1.10106.3.101291.1.1.195
		aip2000c01v1Link1 OBJECT-TYPE
			SYNTAX Ipa2EtherStat
			MAX-ACCESS read-only
			STATUS current
			DESCRIPTION
				"Ethernet conection status"
		::= { aip2000c01v1Entry 195 }

		-- 1.3.6.1.4.1.10106.3.101291.1.1.196
		aip2000c01v1Link1TrapEnable OBJECT-TYPE
			SYNTAX AlarmEnable
			MAX-ACCESS read-write
			STATUS current
			DESCRIPTION
				"Ethernet conection status Trap Enable"
		::= { aip2000c01v1Entry 196 }

		-- 1.3.6.1.4.1.10106.3.101291.1.1.197
		aip2000c01v1System1 OBJECT-TYPE
			SYNTAX Ipa2EtherSys
			MAX-ACCESS read-only
			STATUS current
			DESCRIPTION
				"Ethernet conection system"
		::= { aip2000c01v1Entry 197 }

		-- 1.3.6.1.4.1.10106.3.101291.1.1.198
		aip2000c01v1System1TrapEnable OBJECT-TYPE
			SYNTAX AlarmEnable
			MAX-ACCESS read-write
			STATUS current
			DESCRIPTION
				"Ethernet conection system Trap Enable"
		::= { aip2000c01v1Entry 198 }

		-- 1.3.6.1.4.1.10106.3.101291.1.1.199
		aip2000c01v1Link2 OBJECT-TYPE
			SYNTAX Ipa2EtherStat
			MAX-ACCESS read-only
			STATUS current
			DESCRIPTION
				"Ethernet conection status"
		::= { aip2000c01v1Entry 199 }

		-- 1.3.6.1.4.1.10106.3.101291.1.1.200
		aip2000c01v1Link2TrapEnable OBJECT-TYPE
			SYNTAX AlarmEnable
			MAX-ACCESS read-write
			STATUS current
			DESCRIPTION
				"Ethernet conection status Trap Enable"
		::= { aip2000c01v1Entry 200 }

		-- 1.3.6.1.4.1.10106.3.101291.1.1.201
		aip2000c01v1System2 OBJECT-TYPE
			SYNTAX Ipa2EtherSys
			MAX-ACCESS read-only
			STATUS current
			DESCRIPTION
				"Ethernet conection system"
		::= { aip2000c01v1Entry 201 }

		-- 1.3.6.1.4.1.10106.3.101291.1.1.202
		aip2000c01v1System2TrapEnable OBJECT-TYPE
			SYNTAX AlarmEnable
			MAX-ACCESS read-write
			STATUS current
			DESCRIPTION
				"Ethernet conection system Trap Enable"
		::= { aip2000c01v1Entry 202 }

		-- 1.3.6.1.4.1.10106.3.101291.1.1.203
		aip2000c01v1NoSignal OBJECT-TYPE
			SYNTAX BitFail
			MAX-ACCESS read-only
			STATUS current
			DESCRIPTION
				"There is no SDI signal or the format is not supported"
		::= { aip2000c01v1Entry 203 }

		-- 1.3.6.1.4.1.10106.3.101291.1.1.204
		aip2000c01v1NoSignalTrapEnable OBJECT-TYPE
			SYNTAX AlarmEnable
			MAX-ACCESS read-write
			STATUS current
			DESCRIPTION
				"There is no SDI signal or the format is not supported Trap Enable"
		::= { aip2000c01v1Entry 204 }

		-- 1.3.6.1.4.1.10106.3.101291.1.1.205
		aip2000c01v1Unlock OBJECT-TYPE
			SYNTAX BitFail
			MAX-ACCESS read-only
			STATUS current
			DESCRIPTION
				"Indicates signal unlock fail"
		::= { aip2000c01v1Entry 205 }

		-- 1.3.6.1.4.1.10106.3.101291.1.1.206
		aip2000c01v1UnlockTrapEnable OBJECT-TYPE
			SYNTAX AlarmEnable
			MAX-ACCESS read-write
			STATUS current
			DESCRIPTION
				"Indicates signal unlock fail Trap Enable"
		::= { aip2000c01v1Entry 206 }

		-- 1.3.6.1.4.1.10106.3.101291.1.1.207
		aip2000c01v1EdhError OBJECT-TYPE
			SYNTAX BitFail
			MAX-ACCESS read-only
			STATUS current
			DESCRIPTION
				"There are EDH/CRC errors on SDI signal"
		::= { aip2000c01v1Entry 207 }

		-- 1.3.6.1.4.1.10106.3.101291.1.1.209
		aip2000c01v1Format OBJECT-TYPE
			SYNTAX SdiHd3gFmt3
			MAX-ACCESS read-only
			STATUS current
			DESCRIPTION
				"Indicates the SDI received signal format"
		::= { aip2000c01v1Entry 209 }

		-- 1.3.6.1.4.1.10106.3.101291.1.1.210
		aip2000c01v1FormatTrapEnable OBJECT-TYPE
			SYNTAX AlarmEnable
			MAX-ACCESS read-write
			STATUS current
			DESCRIPTION
				"Indicates the SDI received signal format Trap Enable"
		::= { aip2000c01v1Entry 210 }

		-- 1.3.6.1.4.1.10106.3.101291.1.1.211
		aip2000c01v1PtpState OBJECT-TYPE
			SYNTAX PtpState
			MAX-ACCESS read-only
			STATUS current
			DESCRIPTION
				"Indicates the PTP state"
		::= { aip2000c01v1Entry 211 }

		-- 1.3.6.1.4.1.10106.3.101291.1.1.212
		aip2000c01v1PtpStateTrapEnable OBJECT-TYPE
			SYNTAX AlarmEnable
			MAX-ACCESS read-write
			STATUS current
			DESCRIPTION
				"Indicates the PTP state Trap Enable"
		::= { aip2000c01v1Entry 212 }

		-- 1.3.6.1.4.1.10106.3.101291.1.1.213
		aip2000c01v1TxWorkinStat1 OBJECT-TYPE
			SYNTAX BitFailN
			MAX-ACCESS read-only
			STATUS current
			DESCRIPTION
				"TX1 transmitting"
		::= { aip2000c01v1Entry 213 }

		-- 1.3.6.1.4.1.10106.3.101291.1.1.214
		aip2000c01v1TxWorkinStat1TrapEnable OBJECT-TYPE
			SYNTAX AlarmEnable
			MAX-ACCESS read-write
			STATUS current
			DESCRIPTION
				"TX1 transmitting Trap Enable"
		::= { aip2000c01v1Entry 214 }

		-- 1.3.6.1.4.1.10106.3.101291.1.1.215
		aip2000c01v1ArpValid1 OBJECT-TYPE
			SYNTAX BitFailN
			MAX-ACCESS read-only
			STATUS current
			DESCRIPTION
				"TX1 valid ARP response (Unicast mode)"
		::= { aip2000c01v1Entry 215 }

		-- 1.3.6.1.4.1.10106.3.101291.1.1.216
		aip2000c01v1ArpValid1TrapEnable OBJECT-TYPE
			SYNTAX AlarmEnable
			MAX-ACCESS read-write
			STATUS current
			DESCRIPTION
				"TX1 valid ARP response (Unicast mode) Trap Enable"
		::= { aip2000c01v1Entry 216 }

		-- 1.3.6.1.4.1.10106.3.101291.1.1.217
		aip2000c01v1IcmpError1 OBJECT-TYPE
			SYNTAX BitFailN
			MAX-ACCESS read-only
			STATUS current
			DESCRIPTION
				"TX1 destination unreachable (ICMP destination unrechable packets received)"
		::= { aip2000c01v1Entry 217 }

		-- 1.3.6.1.4.1.10106.3.101291.1.1.218
		aip2000c01v1IcmpError1TrapEnable OBJECT-TYPE
			SYNTAX AlarmEnable
			MAX-ACCESS read-write
			STATUS current
			DESCRIPTION
				"TX1 destination unreachable (ICMP destination unrechable packets received) Trap Enable"
		::= { aip2000c01v1Entry 218 }

		-- 1.3.6.1.4.1.10106.3.101291.1.1.219
		aip2000c01v1TxWorkinStat2 OBJECT-TYPE
			SYNTAX BitFailN
			MAX-ACCESS read-only
			STATUS current
			DESCRIPTION
				"TX2 transmitting"
		::= { aip2000c01v1Entry 219 }

		-- 1.3.6.1.4.1.10106.3.101291.1.1.220
		aip2000c01v1TxWorkinStat2TrapEnable OBJECT-TYPE
			SYNTAX AlarmEnable
			MAX-ACCESS read-write
			STATUS current
			DESCRIPTION
				"TX2 transmitting Trap Enable"
		::= { aip2000c01v1Entry 220 }

		-- 1.3.6.1.4.1.10106.3.101291.1.1.221
		aip2000c01v1ArpValid2 OBJECT-TYPE
			SYNTAX BitFailN
			MAX-ACCESS read-only
			STATUS current
			DESCRIPTION
				"TX2 valid ARP response (Unicast mode)"
		::= { aip2000c01v1Entry 221 }

		-- 1.3.6.1.4.1.10106.3.101291.1.1.222
		aip2000c01v1ArpValid2TrapEnable OBJECT-TYPE
			SYNTAX AlarmEnable
			MAX-ACCESS read-write
			STATUS current
			DESCRIPTION
				"TX2 valid ARP response (Unicast mode) Trap Enable"
		::= { aip2000c01v1Entry 222 }

		-- 1.3.6.1.4.1.10106.3.101291.1.1.223
		aip2000c01v1IcmpError2 OBJECT-TYPE
			SYNTAX BitFailN
			MAX-ACCESS read-only
			STATUS current
			DESCRIPTION
				"TX2 destination unreachable (ICMP destination unrechable packets received)"
		::= { aip2000c01v1Entry 223 }

		-- 1.3.6.1.4.1.10106.3.101291.1.1.224
		aip2000c01v1IcmpError2TrapEnable OBJECT-TYPE
			SYNTAX AlarmEnable
			MAX-ACCESS read-write
			STATUS current
			DESCRIPTION
				"TX2 destination unreachable (ICMP destination unrechable packets received) Trap Enable"
		::= { aip2000c01v1Entry 224 }

		-- 1.3.6.1.4.1.10106.3.101291.1.1.225
		aip2000c01v1TxWorkinStat3 OBJECT-TYPE
			SYNTAX BitFailN
			MAX-ACCESS read-only
			STATUS current
			DESCRIPTION
				"TX3 transmitting"
		::= { aip2000c01v1Entry 225 }

		-- 1.3.6.1.4.1.10106.3.101291.1.1.226
		aip2000c01v1TxWorkinStat3TrapEnable OBJECT-TYPE
			SYNTAX AlarmEnable
			MAX-ACCESS read-write
			STATUS current
			DESCRIPTION
				"TX3 transmitting Trap Enable"
		::= { aip2000c01v1Entry 226 }

		-- 1.3.6.1.4.1.10106.3.101291.1.1.227
		aip2000c01v1ArpValid3 OBJECT-TYPE
			SYNTAX BitFailN
			MAX-ACCESS read-only
			STATUS current
			DESCRIPTION
				"TX3 valid ARP response (Unicast mode)"
		::= { aip2000c01v1Entry 227 }

		-- 1.3.6.1.4.1.10106.3.101291.1.1.228
		aip2000c01v1ArpValid3TrapEnable OBJECT-TYPE
			SYNTAX AlarmEnable
			MAX-ACCESS read-write
			STATUS current
			DESCRIPTION
				"TX3 valid ARP response (Unicast mode) Trap Enable"
		::= { aip2000c01v1Entry 228 }

		-- 1.3.6.1.4.1.10106.3.101291.1.1.229
		aip2000c01v1IcmpError3 OBJECT-TYPE
			SYNTAX BitFailN
			MAX-ACCESS read-only
			STATUS current
			DESCRIPTION
				"TX3 destination unreachable (ICMP destination unrechable packets received)"
		::= { aip2000c01v1Entry 229 }

		-- 1.3.6.1.4.1.10106.3.101291.1.1.230
		aip2000c01v1IcmpError3TrapEnable OBJECT-TYPE
			SYNTAX AlarmEnable
			MAX-ACCESS read-write
			STATUS current
			DESCRIPTION
				"TX3 destination unreachable (ICMP destination unrechable packets received) Trap Enable"
		::= { aip2000c01v1Entry 230 }

		-- 1.3.6.1.4.1.10106.3.101291.1.1.231
		aip2000c01v1TxWorkinStat4 OBJECT-TYPE
			SYNTAX BitFailN
			MAX-ACCESS read-only
			STATUS current
			DESCRIPTION
				"TX4 transmitting"
		::= { aip2000c01v1Entry 231 }

		-- 1.3.6.1.4.1.10106.3.101291.1.1.232
		aip2000c01v1TxWorkinStat4TrapEnable OBJECT-TYPE
			SYNTAX AlarmEnable
			MAX-ACCESS read-write
			STATUS current
			DESCRIPTION
				"TX4 transmitting Trap Enable"
		::= { aip2000c01v1Entry 232 }

		-- 1.3.6.1.4.1.10106.3.101291.1.1.233
		aip2000c01v1ArpValid4 OBJECT-TYPE
			SYNTAX BitFailN
			MAX-ACCESS read-only
			STATUS current
			DESCRIPTION
				"TX4 valid ARP response (Unicast mode)"
		::= { aip2000c01v1Entry 233 }

		-- 1.3.6.1.4.1.10106.3.101291.1.1.234
		aip2000c01v1ArpValid4TrapEnable OBJECT-TYPE
			SYNTAX AlarmEnable
			MAX-ACCESS read-write
			STATUS current
			DESCRIPTION
				"TX4 valid ARP response (Unicast mode) Trap Enable"
		::= { aip2000c01v1Entry 234 }

		-- 1.3.6.1.4.1.10106.3.101291.1.1.235
		aip2000c01v1IcmpError4 OBJECT-TYPE
			SYNTAX BitFailN
			MAX-ACCESS read-only
			STATUS current
			DESCRIPTION
				"TX4 destination unreachable (ICMP destination unrechable packets received)"
		::= { aip2000c01v1Entry 235 }

		-- 1.3.6.1.4.1.10106.3.101291.1.1.236
		aip2000c01v1IcmpError4TrapEnable OBJECT-TYPE
			SYNTAX AlarmEnable
			MAX-ACCESS read-write
			STATUS current
			DESCRIPTION
				"TX4 destination unreachable (ICMP destination unrechable packets received) Trap Enable"
		::= { aip2000c01v1Entry 236 }

		-- 1.3.6.1.4.1.10106.3.101291.1.1.237
		aip2000c01v1AsrcUnlocked1 OBJECT-TYPE
			SYNTAX BitFail
			MAX-ACCESS read-only
			STATUS current
			DESCRIPTION
				"ASRC unlocked (AES67->SDI)"
		::= { aip2000c01v1Entry 237 }

		-- 1.3.6.1.4.1.10106.3.101291.1.1.238
		aip2000c01v1AsrcUnlocked1TrapEnable OBJECT-TYPE
			SYNTAX AlarmEnable
			MAX-ACCESS read-write
			STATUS current
			DESCRIPTION
				"ASRC unlocked (AES67->SDI) Trap Enable"
		::= { aip2000c01v1Entry 238 }

		-- 1.3.6.1.4.1.10106.3.101291.1.1.239
		aip2000c01v1ProcessorStat1 OBJECT-TYPE
			SYNTAX BitFail
			MAX-ACCESS read-only
			STATUS current
			DESCRIPTION
				"Processor syinchronization fail (AES67->SDI)"
		::= { aip2000c01v1Entry 239 }

		-- 1.3.6.1.4.1.10106.3.101291.1.1.240
		aip2000c01v1ProcessorStat1TrapEnable OBJECT-TYPE
			SYNTAX AlarmEnable
			MAX-ACCESS read-write
			STATUS current
			DESCRIPTION
				"Processor syinchronization fail (AES67->SDI) Trap Enable"
		::= { aip2000c01v1Entry 240 }

		-- 1.3.6.1.4.1.10106.3.101291.1.1.241
		aip2000c01v1AsrcUnlocked2 OBJECT-TYPE
			SYNTAX BitFail
			MAX-ACCESS read-only
			STATUS current
			DESCRIPTION
				"ASRC unlocked (SDI->AES67)"
		::= { aip2000c01v1Entry 241 }

		-- 1.3.6.1.4.1.10106.3.101291.1.1.242
		aip2000c01v1AsrcUnlocked2TrapEnable OBJECT-TYPE
			SYNTAX AlarmEnable
			MAX-ACCESS read-write
			STATUS current
			DESCRIPTION
				"ASRC unlocked (SDI->AES67) Trap Enable"
		::= { aip2000c01v1Entry 242 }

		-- 1.3.6.1.4.1.10106.3.101291.1.1.243
		aip2000c01v1ProcessorStat2 OBJECT-TYPE
			SYNTAX BitFail
			MAX-ACCESS read-only
			STATUS current
			DESCRIPTION
				"Processor syinchronization fail (SDI->AES67)"
		::= { aip2000c01v1Entry 243 }

		-- 1.3.6.1.4.1.10106.3.101291.1.1.244
		aip2000c01v1ProcessorStat2TrapEnable OBJECT-TYPE
			SYNTAX AlarmEnable
			MAX-ACCESS read-write
			STATUS current
			DESCRIPTION
				"Processor syinchronization fail (SDI->AES67) Trap Enable"
		::= { aip2000c01v1Entry 244 }

		-- 1.3.6.1.4.1.10106.3.101291.1.1.245
		aip2000c01v1Seamless0 OBJECT-TYPE
			SYNTAX BitFail
			MAX-ACCESS read-only
			STATUS current
			DESCRIPTION
				"Seamless capable RX1/RX2"
		::= { aip2000c01v1Entry 245 }

		-- 1.3.6.1.4.1.10106.3.101291.1.1.246
		aip2000c01v1Seamless0TrapEnable OBJECT-TYPE
			SYNTAX AlarmEnable
			MAX-ACCESS read-write
			STATUS current
			DESCRIPTION
				"Seamless capable RX1/RX2 Trap Enable"
		::= { aip2000c01v1Entry 246 }

		-- 1.3.6.1.4.1.10106.3.101291.1.1.247
		aip2000c01v1Seamless1 OBJECT-TYPE
			SYNTAX BitFail
			MAX-ACCESS read-only
			STATUS current
			DESCRIPTION
				"Seamless capable RX3/RX4"
		::= { aip2000c01v1Entry 247 }

		-- 1.3.6.1.4.1.10106.3.101291.1.1.248
		aip2000c01v1Seamless1TrapEnable OBJECT-TYPE
			SYNTAX AlarmEnable
			MAX-ACCESS read-write
			STATUS current
			DESCRIPTION
				"Seamless capable RX3/RX4 Trap Enable"
		::= { aip2000c01v1Entry 248 }

		-- 1.3.6.1.4.1.10106.3.101291.1.1.249
		aip2000c01v1ClkStatus OBJECT-TYPE
			SYNTAX ClkStatus
			MAX-ACCESS read-only
			STATUS current
			DESCRIPTION
				"Clock status"
		::= { aip2000c01v1Entry 249 }

		-- 1.3.6.1.4.1.10106.3.101291.1.1.250
		aip2000c01v1ClkStatusTrapEnable OBJECT-TYPE
			SYNTAX AlarmEnable
			MAX-ACCESS read-write
			STATUS current
			DESCRIPTION
				"Clock status Trap Enable"
		::= { aip2000c01v1Entry 250 }

		-- 1.3.6.1.4.1.10106.3.101291.1.1.251
		aip2000c01v1Grp1Pres OBJECT-TYPE
			SYNTAX BitFailN
			MAX-ACCESS read-only
			STATUS current
			DESCRIPTION
				"Group 1 presence"
		::= { aip2000c01v1Entry 251 }

		-- 1.3.6.1.4.1.10106.3.101291.1.1.252
		aip2000c01v1Grp1PresTrapEnable OBJECT-TYPE
			SYNTAX AlarmEnable
			MAX-ACCESS read-write
			STATUS current
			DESCRIPTION
				"Group 1 presence Trap Enable"
		::= { aip2000c01v1Entry 252 }

		-- 1.3.6.1.4.1.10106.3.101291.1.1.253
		aip2000c01v1PresenciaMpx OBJECT-TYPE
			SYNTAX BitFailN
			MAX-ACCESS read-only
			STATUS current
			DESCRIPTION
				"MPX presence: channels 1-8"
		::= { aip2000c01v1Entry 253 }

		-- 1.3.6.1.4.1.10106.3.101291.1.1.254
		aip2000c01v1PresenciaMpxTrapEnable OBJECT-TYPE
			SYNTAX AlarmEnable
			MAX-ACCESS read-write
			STATUS current
			DESCRIPTION
				"MPX presence: channels 1-8 Trap Enable"
		::= { aip2000c01v1Entry 254 }

		-- 1.3.6.1.4.1.10106.3.101291.1.1.255
		aip2000c01v1Grp2Pres OBJECT-TYPE
			SYNTAX BitFailN
			MAX-ACCESS read-only
			STATUS current
			DESCRIPTION
				"Group 2 presence"
		::= { aip2000c01v1Entry 255 }

		-- 1.3.6.1.4.1.10106.3.101291.1.1.256
		aip2000c01v1Grp2PresTrapEnable OBJECT-TYPE
			SYNTAX AlarmEnable
			MAX-ACCESS read-write
			STATUS current
			DESCRIPTION
				"Group 2 presence Trap Enable"
		::= { aip2000c01v1Entry 256 }

		-- 1.3.6.1.4.1.10106.3.101291.1.1.257
		aip2000c01v1Grp3Pres OBJECT-TYPE
			SYNTAX BitFailN
			MAX-ACCESS read-only
			STATUS current
			DESCRIPTION
				"Group 3 presence"
		::= { aip2000c01v1Entry 257 }

		-- 1.3.6.1.4.1.10106.3.101291.1.1.258
		aip2000c01v1Grp3PresTrapEnable OBJECT-TYPE
			SYNTAX AlarmEnable
			MAX-ACCESS read-write
			STATUS current
			DESCRIPTION
				"Group 3 presence Trap Enable"
		::= { aip2000c01v1Entry 258 }

		-- 1.3.6.1.4.1.10106.3.101291.1.1.259
		aip2000c01v1Grp4Pres OBJECT-TYPE
			SYNTAX BitFailN
			MAX-ACCESS read-only
			STATUS current
			DESCRIPTION
				"Group 4 presence"
		::= { aip2000c01v1Entry 259 }

		-- 1.3.6.1.4.1.10106.3.101291.1.1.260
		aip2000c01v1Grp4PresTrapEnable OBJECT-TYPE
			SYNTAX AlarmEnable
			MAX-ACCESS read-write
			STATUS current
			DESCRIPTION
				"Group 4 presence Trap Enable"
		::= { aip2000c01v1Entry 260 }

		-- 1.3.6.1.4.1.10106.3.101291.1.1.261
		aip2000c01v1SerialNo OBJECT-TYPE
			SYNTAX SerialNo
			MAX-ACCESS read-only
			STATUS current
			DESCRIPTION
				"Serial number"
		::= { aip2000c01v1Entry 261 }

		-- 1.3.6.1.4.1.10106.3.101291.1.1.263
		aip2000c01v1Priority0 OBJECT-TYPE
			SYNTAX SourceSel0
			MAX-ACCESS read-write
			STATUS current
			DESCRIPTION
				"Prioritary input RX1/RX2"
		::= { aip2000c01v1Entry 263 }

		-- 1.3.6.1.4.1.10106.3.101291.1.1.265
		aip2000c01v1Priority1 OBJECT-TYPE
			SYNTAX SourceSel1
			MAX-ACCESS read-write
			STATUS current
			DESCRIPTION
				"Prioritary input RX3/RX4"
		::= { aip2000c01v1Entry 265 }

		-- 1.3.6.1.4.1.10106.3.101291.1.1.267
		aip2000c01v1RecTime OBJECT-TYPE
			SYNTAX TimeS2
			MAX-ACCESS read-write
			STATUS current
			DESCRIPTION
				"Allows adjust of the recovery time"
		::= { aip2000c01v1Entry 267 }

		-- 1.3.6.1.4.1.10106.3.101291.1.1.269
		aip2000c01v1PtpDelayAsym OBJECT-TYPE
			SYNTAX TimeX1Us
			MAX-ACCESS read-write
			STATUS current
			DESCRIPTION
				"Allows compensating the PTP delay asymmetry"
		::= { aip2000c01v1Entry 269 }

		-- 1.3.6.1.4.1.10106.3.101291.1.1.271
		aip2000c01v1StatReset OBJECT-TYPE
			SYNTAX Bit0No1Yes
			MAX-ACCESS read-write
			STATUS current
			DESCRIPTION
				"Allows reseting the statistics measurements"
		::= { aip2000c01v1Entry 271 }

		-- 1.3.6.1.4.1.10106.3.101291.1.1.273
		aip2000c01v1StatMode OBJECT-TYPE
			SYNTAX Bit01s1Total
			MAX-ACCESS read-write
			STATUS current
			DESCRIPTION
				"Allows selecting the statistics mode"
		::= { aip2000c01v1Entry 273 }

		-- 1.3.6.1.4.1.10106.3.101291.1.1.275
		aip2000c01v1ClockOffset OBJECT-TYPE
			SYNTAX TimeX1Us
			MAX-ACCESS read-only
			STATUS current
			DESCRIPTION
				"Timestamp offset"
		::= { aip2000c01v1Entry 275 }

		-- 1.3.6.1.4.1.10106.3.101291.1.1.277
		aip2000c01v1ClockDelay OBJECT-TYPE
			SYNTAX TimeX1Us
			MAX-ACCESS read-only
			STATUS current
			DESCRIPTION
				"Link delay"
		::= { aip2000c01v1Entry 277 }

		-- 1.3.6.1.4.1.10106.3.101291.1.1.279
		aip2000c01v1Address12En OBJECT-TYPE
			SYNTAX Bit0No1Yes
			MAX-ACCESS read-write
			STATUS current
			DESCRIPTION
				"Interface 2 enable"
		::= { aip2000c01v1Entry 279 }

		-- 1.3.6.1.4.1.10106.3.101291.1.1.281
		aip2000c01v1Address22En OBJECT-TYPE
			SYNTAX Bit0No1Yes
			MAX-ACCESS read-write
			STATUS current
			DESCRIPTION
				"Interface 2 enable"
		::= { aip2000c01v1Entry 281 }

		-- 1.3.6.1.4.1.10106.3.101291.1.1.283
		aip2000c01v1LocalIp3Add3 OBJECT-TYPE
			SYNTAX Uint8
			MAX-ACCESS read-write
			STATUS current
			DESCRIPTION
				"IP address (3)"
		::= { aip2000c01v1Entry 283 }

		-- 1.3.6.1.4.1.10106.3.101291.1.1.285
		aip2000c01v1LocalIp3Add2 OBJECT-TYPE
			SYNTAX Uint8
			MAX-ACCESS read-write
			STATUS current
			DESCRIPTION
				"IP address (2)"
		::= { aip2000c01v1Entry 285 }

		-- 1.3.6.1.4.1.10106.3.101291.1.1.287
		aip2000c01v1LocalIp3Add1 OBJECT-TYPE
			SYNTAX Uint8
			MAX-ACCESS read-write
			STATUS current
			DESCRIPTION
				"IP address (1)"
		::= { aip2000c01v1Entry 287 }

		-- 1.3.6.1.4.1.10106.3.101291.1.1.289
		aip2000c01v1LocalIp3Add0 OBJECT-TYPE
			SYNTAX Uint8
			MAX-ACCESS read-write
			STATUS current
			DESCRIPTION
				"IP address (0)"
		::= { aip2000c01v1Entry 289 }

		-- 1.3.6.1.4.1.10106.3.101291.1.1.291
		aip2000c01v1LocalIp3Msk3 OBJECT-TYPE
			SYNTAX Uint8
			MAX-ACCESS read-write
			STATUS current
			DESCRIPTION
				"IP mask (3)"
		::= { aip2000c01v1Entry 291 }

		-- 1.3.6.1.4.1.10106.3.101291.1.1.293
		aip2000c01v1LocalIp3Msk2 OBJECT-TYPE
			SYNTAX Uint8
			MAX-ACCESS read-write
			STATUS current
			DESCRIPTION
				"IP mask (2)"
		::= { aip2000c01v1Entry 293 }

		-- 1.3.6.1.4.1.10106.3.101291.1.1.295
		aip2000c01v1LocalIp3Msk1 OBJECT-TYPE
			SYNTAX Uint8
			MAX-ACCESS read-write
			STATUS current
			DESCRIPTION
				"IP mask (1)"
		::= { aip2000c01v1Entry 295 }

		-- 1.3.6.1.4.1.10106.3.101291.1.1.297
		aip2000c01v1LocalIp3Msk0 OBJECT-TYPE
			SYNTAX Uint8
			MAX-ACCESS read-write
			STATUS current
			DESCRIPTION
				"IP mask (0)"
		::= { aip2000c01v1Entry 297 }

		-- 1.3.6.1.4.1.10106.3.101291.1.1.299
		aip2000c01v1Vlan3Enable OBJECT-TYPE
			SYNTAX Bit0No1Yes
			MAX-ACCESS read-write
			STATUS current
			DESCRIPTION
				"VLAN Enable"
		::= { aip2000c01v1Entry 299 }

		-- 1.3.6.1.4.1.10106.3.101291.1.1.301
		aip2000c01v1Vlan3Id OBJECT-TYPE
			SYNTAX Uint12
			MAX-ACCESS read-write
			STATUS current
			DESCRIPTION
				"VLAN ID"
		::= { aip2000c01v1Entry 301 }

		-- 1.3.6.1.4.1.10106.3.101291.1.1.303
		aip2000c01v1LocalIp4Add3 OBJECT-TYPE
			SYNTAX Uint8
			MAX-ACCESS read-write
			STATUS current
			DESCRIPTION
				"IP address (3)"
		::= { aip2000c01v1Entry 303 }

		-- 1.3.6.1.4.1.10106.3.101291.1.1.305
		aip2000c01v1LocalIp4Add2 OBJECT-TYPE
			SYNTAX Uint8
			MAX-ACCESS read-write
			STATUS current
			DESCRIPTION
				"IP address (2)"
		::= { aip2000c01v1Entry 305 }

		-- 1.3.6.1.4.1.10106.3.101291.1.1.307
		aip2000c01v1LocalIp4Add1 OBJECT-TYPE
			SYNTAX Uint8
			MAX-ACCESS read-write
			STATUS current
			DESCRIPTION
				"IP address (1)"
		::= { aip2000c01v1Entry 307 }

		-- 1.3.6.1.4.1.10106.3.101291.1.1.309
		aip2000c01v1LocalIp4Add0 OBJECT-TYPE
			SYNTAX Uint8
			MAX-ACCESS read-write
			STATUS current
			DESCRIPTION
				"IP address (0)"
		::= { aip2000c01v1Entry 309 }

		-- 1.3.6.1.4.1.10106.3.101291.1.1.311
		aip2000c01v1LocalIp4Msk3 OBJECT-TYPE
			SYNTAX Uint8
			MAX-ACCESS read-write
			STATUS current
			DESCRIPTION
				"IP mask (3)"
		::= { aip2000c01v1Entry 311 }

		-- 1.3.6.1.4.1.10106.3.101291.1.1.313
		aip2000c01v1LocalIp4Msk2 OBJECT-TYPE
			SYNTAX Uint8
			MAX-ACCESS read-write
			STATUS current
			DESCRIPTION
				"IP mask (2)"
		::= { aip2000c01v1Entry 313 }

		-- 1.3.6.1.4.1.10106.3.101291.1.1.315
		aip2000c01v1LocalIp4Msk1 OBJECT-TYPE
			SYNTAX Uint8
			MAX-ACCESS read-write
			STATUS current
			DESCRIPTION
				"IP mask (1)"
		::= { aip2000c01v1Entry 315 }

		-- 1.3.6.1.4.1.10106.3.101291.1.1.317
		aip2000c01v1LocalIp4Msk0 OBJECT-TYPE
			SYNTAX Uint8
			MAX-ACCESS read-write
			STATUS current
			DESCRIPTION
				"IP mask (0)"
		::= { aip2000c01v1Entry 317 }

		-- 1.3.6.1.4.1.10106.3.101291.1.1.319
		aip2000c01v1Vlan4Enable OBJECT-TYPE
			SYNTAX Bit0No1Yes
			MAX-ACCESS read-write
			STATUS current
			DESCRIPTION
				"VLAN Enable"
		::= { aip2000c01v1Entry 319 }

		-- 1.3.6.1.4.1.10106.3.101291.1.1.321
		aip2000c01v1Vlan4Id OBJECT-TYPE
			SYNTAX Uint12
			MAX-ACCESS read-write
			STATUS current
			DESCRIPTION
				"VLAN ID"
		::= { aip2000c01v1Entry 321 }

		-- 1.3.6.1.4.1.10106.3.101291.1.1.323
		aip2000c01v1RxFail1 OBJECT-TYPE
			SYNTAX BitFail
			MAX-ACCESS read-only
			STATUS current
			DESCRIPTION
				"RX1 stream fail"
		::= { aip2000c01v1Entry 323 }

		-- 1.3.6.1.4.1.10106.3.101291.1.1.325
		aip2000c01v1RxFail2 OBJECT-TYPE
			SYNTAX BitFail
			MAX-ACCESS read-only
			STATUS current
			DESCRIPTION
				"RX2 stream fail"
		::= { aip2000c01v1Entry 325 }

		-- 1.3.6.1.4.1.10106.3.101291.1.1.327
		aip2000c01v1RxFail3 OBJECT-TYPE
			SYNTAX BitFail
			MAX-ACCESS read-only
			STATUS current
			DESCRIPTION
				"RX3 stream fail"
		::= { aip2000c01v1Entry 327 }

		-- 1.3.6.1.4.1.10106.3.101291.1.1.329
		aip2000c01v1RxFail4 OBJECT-TYPE
			SYNTAX BitFail
			MAX-ACCESS read-only
			STATUS current
			DESCRIPTION
				"RX4 stream fail"
		::= { aip2000c01v1Entry 329 }

		-- 1.3.6.1.4.1.10106.3.101291.1.1.331
		aip2000c01v1VlanPriority1 OBJECT-TYPE
			SYNTAX Uint3
			MAX-ACCESS read-write
			STATUS current
			DESCRIPTION
				"VLAN Priority"
		::= { aip2000c01v1Entry 331 }

		-- 1.3.6.1.4.1.10106.3.101291.1.1.333
		aip2000c01v1VlanPriority2 OBJECT-TYPE
			SYNTAX Uint3
			MAX-ACCESS read-write
			STATUS current
			DESCRIPTION
				"VLAN Priority"
		::= { aip2000c01v1Entry 333 }

		-- 1.3.6.1.4.1.10106.3.101291.1.1.335
		aip2000c01v1VlanPriority3 OBJECT-TYPE
			SYNTAX Uint3
			MAX-ACCESS read-write
			STATUS current
			DESCRIPTION
				"VLAN Priority"
		::= { aip2000c01v1Entry 335 }

		-- 1.3.6.1.4.1.10106.3.101291.1.1.337
		aip2000c01v1VlanPriority4 OBJECT-TYPE
			SYNTAX Uint3
			MAX-ACCESS read-write
			STATUS current
			DESCRIPTION
				"VLAN Priority"
		::= { aip2000c01v1Entry 337 }

		-- 1.3.6.1.4.1.10106.3.101291.1.1.339
		aip2000c01v1RxTimeRst OBJECT-TYPE
			SYNTAX TimeS6
			MAX-ACCESS read-only
			STATUS current
			DESCRIPTION
				"Elapsed time since last reset"
		::= { aip2000c01v1Entry 339 }

		-- 1.3.6.1.4.1.10106.3.593001
		asd2008c01v1 OBJECT IDENTIFIER ::= { albalaProducts 593001 }

		-- 1.3.6.1.4.1.10106.3.593001.1
		asd2008c01v1Table  OBJECT-TYPE
			SYNTAX SEQUENCE OF Asd2008c01v1Entry
			MAX-ACCESS not-accessible
			STATUS current
			DESCRIPTION
				"Module  ASD2008C01V1 Table"
			::= { asd2008c01v1 1 }

		-- 1.3.6.1.4.1.10106.3.593001.1.1
		asd2008c01v1Entry  OBJECT-TYPE
			SYNTAX Asd2008c01v1Entry
			MAX-ACCESS not-accessible
			STATUS current
			DESCRIPTION
				"Module ASD2008C01V1 Entry"
			INDEX { asd2008c01v1Index }
			::= { asd2008c01v1Table 1 }

			Asd2008c01v1Entry ::=
			SEQUENCE {
				asd2008c01v1Index
				ModuleIndex,
				asd2008c01v1Invert
				Bit0No1Yes,
				asd2008c01v1CoarseGain
				LevelDbX6,
				asd2008c01v1SampFreq
				Bit0481192,
				asd2008c01v1SampFreqTrapEnable
				AlarmEnable,
				asd2008c01v1BitsPerSamp
				BitsPerSample,
				asd2008c01v1BitsPerSampTrapEnable
				AlarmEnable,
				asd2008c01v1AudClip
				BitFail,
				asd2008c01v1AudClipTrapEnable
				AlarmEnable,
				asd2008c01v1TsLock
				BitFail,
				asd2008c01v1TsLockTrapEnable
				AlarmEnable,
				asd2008c01v1PhaseLock
				BitFail,
				asd2008c01v1PhaseLockTrapEnable
				AlarmEnable,
				asd2008c01v1ChPres1
				BitFail,
				asd2008c01v1ChPres1TrapEnable
				AlarmEnable,
				asd2008c01v1ChPres2
				BitFail,
				asd2008c01v1ChPres2TrapEnable
				AlarmEnable,
				asd2008c01v1ChPres3
				BitFail,
				asd2008c01v1ChPres3TrapEnable
				AlarmEnable,
				asd2008c01v1ChPres4
				BitFail,
				asd2008c01v1ChPres4TrapEnable
				AlarmEnable,
				asd2008c01v1ChPres5
				BitFail,
				asd2008c01v1ChPres5TrapEnable
				AlarmEnable,
				asd2008c01v1ChPres6
				BitFail,
				asd2008c01v1ChPres6TrapEnable
				AlarmEnable,
				asd2008c01v1ChPres7
				BitFail,
				asd2008c01v1ChPres7TrapEnable
				AlarmEnable,
				asd2008c01v1ChPres8
				BitFail,
				asd2008c01v1ChPres8TrapEnable
				AlarmEnable,
				asd2008c01v1SerialNo
				SerialNo
			 }

		-- 1.3.6.1.4.1.10106.3.101291.1.1.1
		asd2008c01v1Index OBJECT-TYPE
			SYNTAX ModuleIndex
			MAX-ACCESS read-only
			STATUS current
			DESCRIPTION
				"Index of ASD2008C01V1 Table"
		::= { asd2008c01v1Entry 1 }

		-- 1.3.6.1.4.1.10106.3.101291.1.1.3
		asd2008c01v1Invert OBJECT-TYPE
			SYNTAX Bit0No1Yes
			MAX-ACCESS read-write
			STATUS current
			DESCRIPTION
				"Enables signal inversion"
		::= { asd2008c01v1Entry 3 }

		-- 1.3.6.1.4.1.10106.3.101291.1.1.5
		asd2008c01v1CoarseGain OBJECT-TYPE
			SYNTAX LevelDbX6
			MAX-ACCESS read-write
			STATUS current
			DESCRIPTION
				"Coarse gain adjust"
		::= { asd2008c01v1Entry 5 }

		-- 1.3.6.1.4.1.10106.3.101291.1.1.7
		asd2008c01v1SampFreq OBJECT-TYPE
			SYNTAX Bit0481192
			MAX-ACCESS read-only
			STATUS current
			DESCRIPTION
				"Sampling frequency used in the received transport stream"
		::= { asd2008c01v1Entry 7 }

		-- 1.3.6.1.4.1.10106.3.101291.1.1.8
		asd2008c01v1SampFreqTrapEnable OBJECT-TYPE
			SYNTAX AlarmEnable
			MAX-ACCESS read-write
			STATUS current
			DESCRIPTION
				"Sampling frequency used in the received transport stream Trap Enable"
		::= { asd2008c01v1Entry 8 }

		-- 1.3.6.1.4.1.10106.3.101291.1.1.9
		asd2008c01v1BitsPerSamp OBJECT-TYPE
			SYNTAX BitsPerSample
			MAX-ACCESS read-only
			STATUS current
			DESCRIPTION
				"Bits per audio sample used in the received transport stream"
		::= { asd2008c01v1Entry 9 }

		-- 1.3.6.1.4.1.10106.3.101291.1.1.10
		asd2008c01v1BitsPerSampTrapEnable OBJECT-TYPE
			SYNTAX AlarmEnable
			MAX-ACCESS read-write
			STATUS current
			DESCRIPTION
				"Bits per audio sample used in the received transport stream Trap Enable"
		::= { asd2008c01v1Entry 10 }

		-- 1.3.6.1.4.1.10106.3.101291.1.1.11
		asd2008c01v1AudClip OBJECT-TYPE
			SYNTAX BitFail
			MAX-ACCESS read-only
			STATUS current
			DESCRIPTION
				"Indicates clipping due to excessive applied gain"
		::= { asd2008c01v1Entry 11 }

		-- 1.3.6.1.4.1.10106.3.101291.1.1.12
		asd2008c01v1AudClipTrapEnable OBJECT-TYPE
			SYNTAX AlarmEnable
			MAX-ACCESS read-write
			STATUS current
			DESCRIPTION
				"Indicates clipping due to excessive applied gain Trap Enable"
		::= { asd2008c01v1Entry 12 }

		-- 1.3.6.1.4.1.10106.3.101291.1.1.13
		asd2008c01v1TsLock OBJECT-TYPE
			SYNTAX BitFail
			MAX-ACCESS read-only
			STATUS current
			DESCRIPTION
				"Transport Stream not present at input or invalid"
		::= { asd2008c01v1Entry 13 }

		-- 1.3.6.1.4.1.10106.3.101291.1.1.14
		asd2008c01v1TsLockTrapEnable OBJECT-TYPE
			SYNTAX AlarmEnable
			MAX-ACCESS read-write
			STATUS current
			DESCRIPTION
				"Transport Stream not present at input or invalid Trap Enable"
		::= { asd2008c01v1Entry 14 }

		-- 1.3.6.1.4.1.10106.3.101291.1.1.15
		asd2008c01v1PhaseLock OBJECT-TYPE
			SYNTAX BitFail
			MAX-ACCESS read-only
			STATUS current
			DESCRIPTION
				"Output not locked to transport stream source"
		::= { asd2008c01v1Entry 15 }

		-- 1.3.6.1.4.1.10106.3.101291.1.1.16
		asd2008c01v1PhaseLockTrapEnable OBJECT-TYPE
			SYNTAX AlarmEnable
			MAX-ACCESS read-write
			STATUS current
			DESCRIPTION
				"Output not locked to transport stream source Trap Enable"
		::= { asd2008c01v1Entry 16 }

		-- 1.3.6.1.4.1.10106.3.101291.1.1.17
		asd2008c01v1ChPres1 OBJECT-TYPE
			SYNTAX BitFail
			MAX-ACCESS read-only
			STATUS current
			DESCRIPTION
				"Channel present in received Transport Stream"
		::= { asd2008c01v1Entry 17 }

		-- 1.3.6.1.4.1.10106.3.101291.1.1.18
		asd2008c01v1ChPres1TrapEnable OBJECT-TYPE
			SYNTAX AlarmEnable
			MAX-ACCESS read-write
			STATUS current
			DESCRIPTION
				"Channel present in received Transport Stream Trap Enable"
		::= { asd2008c01v1Entry 18 }

		-- 1.3.6.1.4.1.10106.3.101291.1.1.19
		asd2008c01v1ChPres2 OBJECT-TYPE
			SYNTAX BitFail
			MAX-ACCESS read-only
			STATUS current
			DESCRIPTION
				"Channel present in received Transport Stream"
		::= { asd2008c01v1Entry 19 }

		-- 1.3.6.1.4.1.10106.3.101291.1.1.20
		asd2008c01v1ChPres2TrapEnable OBJECT-TYPE
			SYNTAX AlarmEnable
			MAX-ACCESS read-write
			STATUS current
			DESCRIPTION
				"Channel present in received Transport Stream Trap Enable"
		::= { asd2008c01v1Entry 20 }

		-- 1.3.6.1.4.1.10106.3.101291.1.1.21
		asd2008c01v1ChPres3 OBJECT-TYPE
			SYNTAX BitFail
			MAX-ACCESS read-only
			STATUS current
			DESCRIPTION
				"Channel present in received Transport Stream"
		::= { asd2008c01v1Entry 21 }

		-- 1.3.6.1.4.1.10106.3.101291.1.1.22
		asd2008c01v1ChPres3TrapEnable OBJECT-TYPE
			SYNTAX AlarmEnable
			MAX-ACCESS read-write
			STATUS current
			DESCRIPTION
				"Channel present in received Transport Stream Trap Enable"
		::= { asd2008c01v1Entry 22 }

		-- 1.3.6.1.4.1.10106.3.101291.1.1.23
		asd2008c01v1ChPres4 OBJECT-TYPE
			SYNTAX BitFail
			MAX-ACCESS read-only
			STATUS current
			DESCRIPTION
				"Channel present in received Transport Stream"
		::= { asd2008c01v1Entry 23 }

		-- 1.3.6.1.4.1.10106.3.101291.1.1.24
		asd2008c01v1ChPres4TrapEnable OBJECT-TYPE
			SYNTAX AlarmEnable
			MAX-ACCESS read-write
			STATUS current
			DESCRIPTION
				"Channel present in received Transport Stream Trap Enable"
		::= { asd2008c01v1Entry 24 }

		-- 1.3.6.1.4.1.10106.3.101291.1.1.25
		asd2008c01v1ChPres5 OBJECT-TYPE
			SYNTAX BitFail
			MAX-ACCESS read-only
			STATUS current
			DESCRIPTION
				"Channel present in received Transport Stream"
		::= { asd2008c01v1Entry 25 }

		-- 1.3.6.1.4.1.10106.3.101291.1.1.26
		asd2008c01v1ChPres5TrapEnable OBJECT-TYPE
			SYNTAX AlarmEnable
			MAX-ACCESS read-write
			STATUS current
			DESCRIPTION
				"Channel present in received Transport Stream Trap Enable"
		::= { asd2008c01v1Entry 26 }

		-- 1.3.6.1.4.1.10106.3.101291.1.1.27
		asd2008c01v1ChPres6 OBJECT-TYPE
			SYNTAX BitFail
			MAX-ACCESS read-only
			STATUS current
			DESCRIPTION
				"Channel present in received Transport Stream"
		::= { asd2008c01v1Entry 27 }

		-- 1.3.6.1.4.1.10106.3.101291.1.1.28
		asd2008c01v1ChPres6TrapEnable OBJECT-TYPE
			SYNTAX AlarmEnable
			MAX-ACCESS read-write
			STATUS current
			DESCRIPTION
				"Channel present in received Transport Stream Trap Enable"
		::= { asd2008c01v1Entry 28 }

		-- 1.3.6.1.4.1.10106.3.101291.1.1.29
		asd2008c01v1ChPres7 OBJECT-TYPE
			SYNTAX BitFail
			MAX-ACCESS read-only
			STATUS current
			DESCRIPTION
				"Channel present in received Transport Stream"
		::= { asd2008c01v1Entry 29 }

		-- 1.3.6.1.4.1.10106.3.101291.1.1.30
		asd2008c01v1ChPres7TrapEnable OBJECT-TYPE
			SYNTAX AlarmEnable
			MAX-ACCESS read-write
			STATUS current
			DESCRIPTION
				"Channel present in received Transport Stream Trap Enable"
		::= { asd2008c01v1Entry 30 }

		-- 1.3.6.1.4.1.10106.3.101291.1.1.31
		asd2008c01v1ChPres8 OBJECT-TYPE
			SYNTAX BitFail
			MAX-ACCESS read-only
			STATUS current
			DESCRIPTION
				"Channel present in received Transport Stream"
		::= { asd2008c01v1Entry 31 }

		-- 1.3.6.1.4.1.10106.3.101291.1.1.32
		asd2008c01v1ChPres8TrapEnable OBJECT-TYPE
			SYNTAX AlarmEnable
			MAX-ACCESS read-write
			STATUS current
			DESCRIPTION
				"Channel present in received Transport Stream Trap Enable"
		::= { asd2008c01v1Entry 32 }

		-- 1.3.6.1.4.1.10106.3.101291.1.1.33
		asd2008c01v1SerialNo OBJECT-TYPE
			SYNTAX SerialNo
			MAX-ACCESS read-only
			STATUS current
			DESCRIPTION
				"Serial number"
		::= { asd2008c01v1Entry 33 }

		-- 1.3.6.1.4.1.10106.3.599301
		ded2008c01v1 OBJECT IDENTIFIER ::= { albalaProducts 599301 }

		-- 1.3.6.1.4.1.10106.3.599301.1
		ded2008c01v1Table  OBJECT-TYPE
			SYNTAX SEQUENCE OF Ded2008c01v1Entry
			MAX-ACCESS not-accessible
			STATUS current
			DESCRIPTION
				"Module  DED2008C01V1 Table"
			::= { ded2008c01v1 1 }

		-- 1.3.6.1.4.1.10106.3.599301.1.1
		ded2008c01v1Entry  OBJECT-TYPE
			SYNTAX Ded2008c01v1Entry
			MAX-ACCESS not-accessible
			STATUS current
			DESCRIPTION
				"Module DED2008C01V1 Entry"
			INDEX { ded2008c01v1Index }
			::= { ded2008c01v1Table 1 }

			Ded2008c01v1Entry ::=
			SEQUENCE {
				ded2008c01v1Index
				ModuleIndex,
				ded2008c01v1AesIoMode
				IoMode,
				ded2008c01v1ChSel
				AudioChannels2,
				ded2008c01v1SdiInDis
				Bit0No1Yes,
				ded2008c01v1In1Mode
				Bit0No1Yes,
				ded2008c01v1In2Mode
				Bit0No1Yes,
				ded2008c01v1In3Mode
				Bit0No1Yes,
				ded2008c01v1In4Mode
				Bit0No1Yes,
				ded2008c01v1In5Mode
				Bit0No1Yes,
				ded2008c01v1In6Mode
				Bit0No1Yes,
				ded2008c01v1In7Mode
				Bit0No1Yes,
				ded2008c01v1In8Mode
				Bit0No1Yes,
				ded2008c01v1Out1AsrcEn
				Bit0No1Yes,
				ded2008c01v1Out2AsrcEn
				Bit0No1Yes,
				ded2008c01v1Out3AsrcEn
				Bit0No1Yes,
				ded2008c01v1Out4AsrcEn
				Bit0No1Yes,
				ded2008c01v1In1En
				Bit0No1Yes,
				ded2008c01v1In2En
				Bit0No1Yes,
				ded2008c01v1In3En
				Bit0No1Yes,
				ded2008c01v1In4En
				Bit0No1Yes,
				ded2008c01v1In5En
				Bit0No1Yes,
				ded2008c01v1In6En
				Bit0No1Yes,
				ded2008c01v1In7En
				Bit0No1Yes,
				ded2008c01v1In8En
				Bit0No1Yes,
				ded2008c01v1Out1En
				Bit0No1Yes,
				ded2008c01v1Out2En
				Bit0No1Yes,
				ded2008c01v1Out3En
				Bit0No1Yes,
				ded2008c01v1Out4En
				Bit0No1Yes,
				ded2008c01v1Out5En
				Bit0No1Yes,
				ded2008c01v1Out6En
				Bit0No1Yes,
				ded2008c01v1Out7En
				Bit0No1Yes,
				ded2008c01v1Out8En
				Bit0No1Yes,
				ded2008c01v1SdiFmt
				Bit05251625,
				ded2008c01v1SdiInFail
				BitFail,
				ded2008c01v1SdiInFailTrapEnable
				AlarmEnable,
				ded2008c01v1SdiG1Fail
				BitFail,
				ded2008c01v1SdiG1FailTrapEnable
				AlarmEnable,
				ded2008c01v1SdiG2Fail
				BitFail,
				ded2008c01v1SdiG2FailTrapEnable
				AlarmEnable,
				ded2008c01v1SdiG3Fail
				BitFail,
				ded2008c01v1SdiG3FailTrapEnable
				AlarmEnable,
				ded2008c01v1SdiG4Fail
				BitFail,
				ded2008c01v1SdiG4FailTrapEnable
				AlarmEnable,
				ded2008c01v1Ref27mFail
				BitFail,
				ded2008c01v1Ref27mFailTrapEnable
				AlarmEnable,
				ded2008c01v1AudioProcFail
				BitFail,
				ded2008c01v1AudioProcFailTrapEnable
				AlarmEnable,
				ded2008c01v1In1AudFail
				BitFail,
				ded2008c01v1In1AudFailTrapEnable
				AlarmEnable,
				ded2008c01v1In1RefFail
				BitFail,
				ded2008c01v1In1RefFailTrapEnable
				AlarmEnable,
				ded2008c01v1In2AudFail
				BitFail,
				ded2008c01v1In2AudFailTrapEnable
				AlarmEnable,
				ded2008c01v1In2RefFail
				BitFail,
				ded2008c01v1In2RefFailTrapEnable
				AlarmEnable,
				ded2008c01v1In3AudFail
				BitFail,
				ded2008c01v1In3AudFailTrapEnable
				AlarmEnable,
				ded2008c01v1In3RefFail
				BitFail,
				ded2008c01v1In3RefFailTrapEnable
				AlarmEnable,
				ded2008c01v1In4AudFail
				BitFail,
				ded2008c01v1In4AudFailTrapEnable
				AlarmEnable,
				ded2008c01v1In4RefFail
				BitFail,
				ded2008c01v1In4RefFailTrapEnable
				AlarmEnable,
				ded2008c01v1In5AudFail
				BitFail,
				ded2008c01v1In5AudFailTrapEnable
				AlarmEnable,
				ded2008c01v1In6AudFail
				BitFail,
				ded2008c01v1In6AudFailTrapEnable
				AlarmEnable,
				ded2008c01v1In7AudFail
				BitFail,
				ded2008c01v1In7AudFailTrapEnable
				AlarmEnable,
				ded2008c01v1In8AudFail
				BitFail,
				ded2008c01v1In8AudFailTrapEnable
				AlarmEnable,
				ded2008c01v1In1FreqFail
				BitFail,
				ded2008c01v1In2FreqFail
				BitFail,
				ded2008c01v1In3FreqFail
				BitFail,
				ded2008c01v1In4FreqFail
				BitFail,
				ded2008c01v1In5FreqFail
				BitFail,
				ded2008c01v1In6FreqFail
				BitFail,
				ded2008c01v1In7FreqFail
				BitFail,
				ded2008c01v1In8FreqFail
				BitFail,
				ded2008c01v1SdiInFmt
				Bit05251625,
				ded2008c01v1SerialNo
				SerialNo
			 }

		-- 1.3.6.1.4.1.10106.3.101291.1.1.1
		ded2008c01v1Index OBJECT-TYPE
			SYNTAX ModuleIndex
			MAX-ACCESS read-only
			STATUS current
			DESCRIPTION
				"Index of DED2008C01V1 Table"
		::= { ded2008c01v1Entry 1 }

		-- 1.3.6.1.4.1.10106.3.101291.1.1.3
		ded2008c01v1AesIoMode OBJECT-TYPE
			SYNTAX IoMode
			MAX-ACCESS read-write
			STATUS current
			DESCRIPTION
				"Mode of operation"
		::= { ded2008c01v1Entry 3 }

		-- 1.3.6.1.4.1.10106.3.101291.1.1.5
		ded2008c01v1ChSel OBJECT-TYPE
			SYNTAX AudioChannels2
			MAX-ACCESS read-write
			STATUS current
			DESCRIPTION
				"Selects the subset of audio channels in the SDI signal that will be processed"
		::= { ded2008c01v1Entry 5 }

		-- 1.3.6.1.4.1.10106.3.101291.1.1.7
		ded2008c01v1SdiInDis OBJECT-TYPE
			SYNTAX Bit0No1Yes
			MAX-ACCESS read-write
			STATUS current
			DESCRIPTION
				"Disable SDI input"
		::= { ded2008c01v1Entry 7 }

		-- 1.3.6.1.4.1.10106.3.101291.1.1.9
		ded2008c01v1In1Mode OBJECT-TYPE
			SYNTAX Bit0No1Yes
			MAX-ACCESS read-write
			STATUS current
			DESCRIPTION
				"Enable ASRC in IN1"
		::= { ded2008c01v1Entry 9 }

		-- 1.3.6.1.4.1.10106.3.101291.1.1.11
		ded2008c01v1In2Mode OBJECT-TYPE
			SYNTAX Bit0No1Yes
			MAX-ACCESS read-write
			STATUS current
			DESCRIPTION
				"Enable ASRC in IN2"
		::= { ded2008c01v1Entry 11 }

		-- 1.3.6.1.4.1.10106.3.101291.1.1.13
		ded2008c01v1In3Mode OBJECT-TYPE
			SYNTAX Bit0No1Yes
			MAX-ACCESS read-write
			STATUS current
			DESCRIPTION
				"Enable ASRC in IN3"
		::= { ded2008c01v1Entry 13 }

		-- 1.3.6.1.4.1.10106.3.101291.1.1.15
		ded2008c01v1In4Mode OBJECT-TYPE
			SYNTAX Bit0No1Yes
			MAX-ACCESS read-write
			STATUS current
			DESCRIPTION
				"Enable ASRC in IN4"
		::= { ded2008c01v1Entry 15 }

		-- 1.3.6.1.4.1.10106.3.101291.1.1.17
		ded2008c01v1In5Mode OBJECT-TYPE
			SYNTAX Bit0No1Yes
			MAX-ACCESS read-write
			STATUS current
			DESCRIPTION
				"Enable ASRC in IN5"
		::= { ded2008c01v1Entry 17 }

		-- 1.3.6.1.4.1.10106.3.101291.1.1.19
		ded2008c01v1In6Mode OBJECT-TYPE
			SYNTAX Bit0No1Yes
			MAX-ACCESS read-write
			STATUS current
			DESCRIPTION
				"Enable ASRC in IN6"
		::= { ded2008c01v1Entry 19 }

		-- 1.3.6.1.4.1.10106.3.101291.1.1.21
		ded2008c01v1In7Mode OBJECT-TYPE
			SYNTAX Bit0No1Yes
			MAX-ACCESS read-write
			STATUS current
			DESCRIPTION
				"Enable ASRC in IN7"
		::= { ded2008c01v1Entry 21 }

		-- 1.3.6.1.4.1.10106.3.101291.1.1.23
		ded2008c01v1In8Mode OBJECT-TYPE
			SYNTAX Bit0No1Yes
			MAX-ACCESS read-write
			STATUS current
			DESCRIPTION
				"Enable ASRC in IN8"
		::= { ded2008c01v1Entry 23 }

		-- 1.3.6.1.4.1.10106.3.101291.1.1.25
		ded2008c01v1Out1AsrcEn OBJECT-TYPE
			SYNTAX Bit0No1Yes
			MAX-ACCESS read-write
			STATUS current
			DESCRIPTION
				"Enables ASRC in OUT1"
		::= { ded2008c01v1Entry 25 }

		-- 1.3.6.1.4.1.10106.3.101291.1.1.27
		ded2008c01v1Out2AsrcEn OBJECT-TYPE
			SYNTAX Bit0No1Yes
			MAX-ACCESS read-write
			STATUS current
			DESCRIPTION
				"Enables ASRC in OUT2"
		::= { ded2008c01v1Entry 27 }

		-- 1.3.6.1.4.1.10106.3.101291.1.1.29
		ded2008c01v1Out3AsrcEn OBJECT-TYPE
			SYNTAX Bit0No1Yes
			MAX-ACCESS read-write
			STATUS current
			DESCRIPTION
				"Enables ASRC in OUT3"
		::= { ded2008c01v1Entry 29 }

		-- 1.3.6.1.4.1.10106.3.101291.1.1.31
		ded2008c01v1Out4AsrcEn OBJECT-TYPE
			SYNTAX Bit0No1Yes
			MAX-ACCESS read-write
			STATUS current
			DESCRIPTION
				"Enables ASRC in OUT4"
		::= { ded2008c01v1Entry 31 }

		-- 1.3.6.1.4.1.10106.3.101291.1.1.33
		ded2008c01v1In1En OBJECT-TYPE
			SYNTAX Bit0No1Yes
			MAX-ACCESS read-write
			STATUS current
			DESCRIPTION
				"Embed IN1 in G1P0"
		::= { ded2008c01v1Entry 33 }

		-- 1.3.6.1.4.1.10106.3.101291.1.1.35
		ded2008c01v1In2En OBJECT-TYPE
			SYNTAX Bit0No1Yes
			MAX-ACCESS read-write
			STATUS current
			DESCRIPTION
				"Embed IN2 in G1P1"
		::= { ded2008c01v1Entry 35 }

		-- 1.3.6.1.4.1.10106.3.101291.1.1.37
		ded2008c01v1In3En OBJECT-TYPE
			SYNTAX Bit0No1Yes
			MAX-ACCESS read-write
			STATUS current
			DESCRIPTION
				"Embed IN3 in G2P0"
		::= { ded2008c01v1Entry 37 }

		-- 1.3.6.1.4.1.10106.3.101291.1.1.39
		ded2008c01v1In4En OBJECT-TYPE
			SYNTAX Bit0No1Yes
			MAX-ACCESS read-write
			STATUS current
			DESCRIPTION
				"Embed IN4 in G2P1"
		::= { ded2008c01v1Entry 39 }

		-- 1.3.6.1.4.1.10106.3.101291.1.1.41
		ded2008c01v1In5En OBJECT-TYPE
			SYNTAX Bit0No1Yes
			MAX-ACCESS read-write
			STATUS current
			DESCRIPTION
				"Embed IN5 in G3P0"
		::= { ded2008c01v1Entry 41 }

		-- 1.3.6.1.4.1.10106.3.101291.1.1.43
		ded2008c01v1In6En OBJECT-TYPE
			SYNTAX Bit0No1Yes
			MAX-ACCESS read-write
			STATUS current
			DESCRIPTION
				"Embed IN6 in G3P1"
		::= { ded2008c01v1Entry 43 }

		-- 1.3.6.1.4.1.10106.3.101291.1.1.45
		ded2008c01v1In7En OBJECT-TYPE
			SYNTAX Bit0No1Yes
			MAX-ACCESS read-write
			STATUS current
			DESCRIPTION
				"Embed IN7 in G4P0"
		::= { ded2008c01v1Entry 45 }

		-- 1.3.6.1.4.1.10106.3.101291.1.1.47
		ded2008c01v1In8En OBJECT-TYPE
			SYNTAX Bit0No1Yes
			MAX-ACCESS read-write
			STATUS current
			DESCRIPTION
				"Embed IN8 in G4P1"
		::= { ded2008c01v1Entry 47 }

		-- 1.3.6.1.4.1.10106.3.101291.1.1.49
		ded2008c01v1Out1En OBJECT-TYPE
			SYNTAX Bit0No1Yes
			MAX-ACCESS read-write
			STATUS current
			DESCRIPTION
				"Enables OUT1 output"
		::= { ded2008c01v1Entry 49 }

		-- 1.3.6.1.4.1.10106.3.101291.1.1.51
		ded2008c01v1Out2En OBJECT-TYPE
			SYNTAX Bit0No1Yes
			MAX-ACCESS read-write
			STATUS current
			DESCRIPTION
				"Enables OUT2 output"
		::= { ded2008c01v1Entry 51 }

		-- 1.3.6.1.4.1.10106.3.101291.1.1.53
		ded2008c01v1Out3En OBJECT-TYPE
			SYNTAX Bit0No1Yes
			MAX-ACCESS read-write
			STATUS current
			DESCRIPTION
				"Enables OUT3 output"
		::= { ded2008c01v1Entry 53 }

		-- 1.3.6.1.4.1.10106.3.101291.1.1.55
		ded2008c01v1Out4En OBJECT-TYPE
			SYNTAX Bit0No1Yes
			MAX-ACCESS read-write
			STATUS current
			DESCRIPTION
				"Enables OUT4 output"
		::= { ded2008c01v1Entry 55 }

		-- 1.3.6.1.4.1.10106.3.101291.1.1.57
		ded2008c01v1Out5En OBJECT-TYPE
			SYNTAX Bit0No1Yes
			MAX-ACCESS read-write
			STATUS current
			DESCRIPTION
				"Enables OUT5 output"
		::= { ded2008c01v1Entry 57 }

		-- 1.3.6.1.4.1.10106.3.101291.1.1.59
		ded2008c01v1Out6En OBJECT-TYPE
			SYNTAX Bit0No1Yes
			MAX-ACCESS read-write
			STATUS current
			DESCRIPTION
				"Enables OUT6 output"
		::= { ded2008c01v1Entry 59 }

		-- 1.3.6.1.4.1.10106.3.101291.1.1.61
		ded2008c01v1Out7En OBJECT-TYPE
			SYNTAX Bit0No1Yes
			MAX-ACCESS read-write
			STATUS current
			DESCRIPTION
				"Enables OUT7 output"
		::= { ded2008c01v1Entry 61 }

		-- 1.3.6.1.4.1.10106.3.101291.1.1.63
		ded2008c01v1Out8En OBJECT-TYPE
			SYNTAX Bit0No1Yes
			MAX-ACCESS read-write
			STATUS current
			DESCRIPTION
				"Enables OUT8 output"
		::= { ded2008c01v1Entry 63 }

		-- 1.3.6.1.4.1.10106.3.101291.1.1.65
		ded2008c01v1SdiFmt OBJECT-TYPE
			SYNTAX Bit05251625
			MAX-ACCESS read-write
			STATUS current
			DESCRIPTION
				"SDI output format to be used before an SDI input is detected"
		::= { ded2008c01v1Entry 65 }

		-- 1.3.6.1.4.1.10106.3.101291.1.1.67
		ded2008c01v1SdiInFail OBJECT-TYPE
			SYNTAX BitFail
			MAX-ACCESS read-only
			STATUS current
			DESCRIPTION
				"No signal present in SDI input"
		::= { ded2008c01v1Entry 67 }

		-- 1.3.6.1.4.1.10106.3.101291.1.1.68
		ded2008c01v1SdiInFailTrapEnable OBJECT-TYPE
			SYNTAX AlarmEnable
			MAX-ACCESS read-write
			STATUS current
			DESCRIPTION
				"No signal present in SDI input Trap Enable"
		::= { ded2008c01v1Entry 68 }

		-- 1.3.6.1.4.1.10106.3.101291.1.1.69
		ded2008c01v1SdiG1Fail OBJECT-TYPE
			SYNTAX BitFail
			MAX-ACCESS read-only
			STATUS current
			DESCRIPTION
				"Audio group 1 not present in input SDI signal"
		::= { ded2008c01v1Entry 69 }

		-- 1.3.6.1.4.1.10106.3.101291.1.1.70
		ded2008c01v1SdiG1FailTrapEnable OBJECT-TYPE
			SYNTAX AlarmEnable
			MAX-ACCESS read-write
			STATUS current
			DESCRIPTION
				"Audio group 1 not present in input SDI signal Trap Enable"
		::= { ded2008c01v1Entry 70 }

		-- 1.3.6.1.4.1.10106.3.101291.1.1.71
		ded2008c01v1SdiG2Fail OBJECT-TYPE
			SYNTAX BitFail
			MAX-ACCESS read-only
			STATUS current
			DESCRIPTION
				"Audio group 2 not present in input SDI signal"
		::= { ded2008c01v1Entry 71 }

		-- 1.3.6.1.4.1.10106.3.101291.1.1.72
		ded2008c01v1SdiG2FailTrapEnable OBJECT-TYPE
			SYNTAX AlarmEnable
			MAX-ACCESS read-write
			STATUS current
			DESCRIPTION
				"Audio group 2 not present in input SDI signal Trap Enable"
		::= { ded2008c01v1Entry 72 }

		-- 1.3.6.1.4.1.10106.3.101291.1.1.73
		ded2008c01v1SdiG3Fail OBJECT-TYPE
			SYNTAX BitFail
			MAX-ACCESS read-only
			STATUS current
			DESCRIPTION
				"Audio group 3 not present in input SDI signal"
		::= { ded2008c01v1Entry 73 }

		-- 1.3.6.1.4.1.10106.3.101291.1.1.74
		ded2008c01v1SdiG3FailTrapEnable OBJECT-TYPE
			SYNTAX AlarmEnable
			MAX-ACCESS read-write
			STATUS current
			DESCRIPTION
				"Audio group 3 not present in input SDI signal Trap Enable"
		::= { ded2008c01v1Entry 74 }

		-- 1.3.6.1.4.1.10106.3.101291.1.1.75
		ded2008c01v1SdiG4Fail OBJECT-TYPE
			SYNTAX BitFail
			MAX-ACCESS read-only
			STATUS current
			DESCRIPTION
				"Audio group 4 not present in input SDI signal"
		::= { ded2008c01v1Entry 75 }

		-- 1.3.6.1.4.1.10106.3.101291.1.1.76
		ded2008c01v1SdiG4FailTrapEnable OBJECT-TYPE
			SYNTAX AlarmEnable
			MAX-ACCESS read-write
			STATUS current
			DESCRIPTION
				"Audio group 4 not present in input SDI signal Trap Enable"
		::= { ded2008c01v1Entry 76 }

		-- 1.3.6.1.4.1.10106.3.101291.1.1.77
		ded2008c01v1Ref27mFail OBJECT-TYPE
			SYNTAX BitFail
			MAX-ACCESS read-only
			STATUS current
			DESCRIPTION
				"No 27 MHz reference coming from slot on the right"
		::= { ded2008c01v1Entry 77 }

		-- 1.3.6.1.4.1.10106.3.101291.1.1.78
		ded2008c01v1Ref27mFailTrapEnable OBJECT-TYPE
			SYNTAX AlarmEnable
			MAX-ACCESS read-write
			STATUS current
			DESCRIPTION
				"No 27 MHz reference coming from slot on the right Trap Enable"
		::= { ded2008c01v1Entry 78 }

		-- 1.3.6.1.4.1.10106.3.101291.1.1.79
		ded2008c01v1AudioProcFail OBJECT-TYPE
			SYNTAX BitFail
			MAX-ACCESS read-only
			STATUS current
			DESCRIPTION
				"Indicates an invalid configuration or input error"
		::= { ded2008c01v1Entry 79 }

		-- 1.3.6.1.4.1.10106.3.101291.1.1.80
		ded2008c01v1AudioProcFailTrapEnable OBJECT-TYPE
			SYNTAX AlarmEnable
			MAX-ACCESS read-write
			STATUS current
			DESCRIPTION
				"Indicates an invalid configuration or input error Trap Enable"
		::= { ded2008c01v1Entry 80 }

		-- 1.3.6.1.4.1.10106.3.101291.1.1.81
		ded2008c01v1In1AudFail OBJECT-TYPE
			SYNTAX BitFail
			MAX-ACCESS read-only
			STATUS current
			DESCRIPTION
				"No signal in IN1 input"
		::= { ded2008c01v1Entry 81 }

		-- 1.3.6.1.4.1.10106.3.101291.1.1.82
		ded2008c01v1In1AudFailTrapEnable OBJECT-TYPE
			SYNTAX AlarmEnable
			MAX-ACCESS read-write
			STATUS current
			DESCRIPTION
				"No signal in IN1 input Trap Enable"
		::= { ded2008c01v1Entry 82 }

		-- 1.3.6.1.4.1.10106.3.101291.1.1.83
		ded2008c01v1In1RefFail OBJECT-TYPE
			SYNTAX BitFail
			MAX-ACCESS read-only
			STATUS current
			DESCRIPTION
				"No reference present in IN1"
		::= { ded2008c01v1Entry 83 }

		-- 1.3.6.1.4.1.10106.3.101291.1.1.84
		ded2008c01v1In1RefFailTrapEnable OBJECT-TYPE
			SYNTAX AlarmEnable
			MAX-ACCESS read-write
			STATUS current
			DESCRIPTION
				"No reference present in IN1 Trap Enable"
		::= { ded2008c01v1Entry 84 }

		-- 1.3.6.1.4.1.10106.3.101291.1.1.85
		ded2008c01v1In2AudFail OBJECT-TYPE
			SYNTAX BitFail
			MAX-ACCESS read-only
			STATUS current
			DESCRIPTION
				"No signal in IN2 input"
		::= { ded2008c01v1Entry 85 }

		-- 1.3.6.1.4.1.10106.3.101291.1.1.86
		ded2008c01v1In2AudFailTrapEnable OBJECT-TYPE
			SYNTAX AlarmEnable
			MAX-ACCESS read-write
			STATUS current
			DESCRIPTION
				"No signal in IN2 input Trap Enable"
		::= { ded2008c01v1Entry 86 }

		-- 1.3.6.1.4.1.10106.3.101291.1.1.87
		ded2008c01v1In2RefFail OBJECT-TYPE
			SYNTAX BitFail
			MAX-ACCESS read-only
			STATUS current
			DESCRIPTION
				"No reference present in IN2"
		::= { ded2008c01v1Entry 87 }

		-- 1.3.6.1.4.1.10106.3.101291.1.1.88
		ded2008c01v1In2RefFailTrapEnable OBJECT-TYPE
			SYNTAX AlarmEnable
			MAX-ACCESS read-write
			STATUS current
			DESCRIPTION
				"No reference present in IN2 Trap Enable"
		::= { ded2008c01v1Entry 88 }

		-- 1.3.6.1.4.1.10106.3.101291.1.1.89
		ded2008c01v1In3AudFail OBJECT-TYPE
			SYNTAX BitFail
			MAX-ACCESS read-only
			STATUS current
			DESCRIPTION
				"No signal in IN3 input"
		::= { ded2008c01v1Entry 89 }

		-- 1.3.6.1.4.1.10106.3.101291.1.1.90
		ded2008c01v1In3AudFailTrapEnable OBJECT-TYPE
			SYNTAX AlarmEnable
			MAX-ACCESS read-write
			STATUS current
			DESCRIPTION
				"No signal in IN3 input Trap Enable"
		::= { ded2008c01v1Entry 90 }

		-- 1.3.6.1.4.1.10106.3.101291.1.1.91
		ded2008c01v1In3RefFail OBJECT-TYPE
			SYNTAX BitFail
			MAX-ACCESS read-only
			STATUS current
			DESCRIPTION
				"No reference present in IN3"
		::= { ded2008c01v1Entry 91 }

		-- 1.3.6.1.4.1.10106.3.101291.1.1.92
		ded2008c01v1In3RefFailTrapEnable OBJECT-TYPE
			SYNTAX AlarmEnable
			MAX-ACCESS read-write
			STATUS current
			DESCRIPTION
				"No reference present in IN3 Trap Enable"
		::= { ded2008c01v1Entry 92 }

		-- 1.3.6.1.4.1.10106.3.101291.1.1.93
		ded2008c01v1In4AudFail OBJECT-TYPE
			SYNTAX BitFail
			MAX-ACCESS read-only
			STATUS current
			DESCRIPTION
				"No signal in IN4 input"
		::= { ded2008c01v1Entry 93 }

		-- 1.3.6.1.4.1.10106.3.101291.1.1.94
		ded2008c01v1In4AudFailTrapEnable OBJECT-TYPE
			SYNTAX AlarmEnable
			MAX-ACCESS read-write
			STATUS current
			DESCRIPTION
				"No signal in IN4 input Trap Enable"
		::= { ded2008c01v1Entry 94 }

		-- 1.3.6.1.4.1.10106.3.101291.1.1.95
		ded2008c01v1In4RefFail OBJECT-TYPE
			SYNTAX BitFail
			MAX-ACCESS read-only
			STATUS current
			DESCRIPTION
				"No reference present in IN4"
		::= { ded2008c01v1Entry 95 }

		-- 1.3.6.1.4.1.10106.3.101291.1.1.96
		ded2008c01v1In4RefFailTrapEnable OBJECT-TYPE
			SYNTAX AlarmEnable
			MAX-ACCESS read-write
			STATUS current
			DESCRIPTION
				"No reference present in IN4 Trap Enable"
		::= { ded2008c01v1Entry 96 }

		-- 1.3.6.1.4.1.10106.3.101291.1.1.97
		ded2008c01v1In5AudFail OBJECT-TYPE
			SYNTAX BitFail
			MAX-ACCESS read-only
			STATUS current
			DESCRIPTION
				"No signal in IN5 input"
		::= { ded2008c01v1Entry 97 }

		-- 1.3.6.1.4.1.10106.3.101291.1.1.98
		ded2008c01v1In5AudFailTrapEnable OBJECT-TYPE
			SYNTAX AlarmEnable
			MAX-ACCESS read-write
			STATUS current
			DESCRIPTION
				"No signal in IN5 input Trap Enable"
		::= { ded2008c01v1Entry 98 }

		-- 1.3.6.1.4.1.10106.3.101291.1.1.99
		ded2008c01v1In6AudFail OBJECT-TYPE
			SYNTAX BitFail
			MAX-ACCESS read-only
			STATUS current
			DESCRIPTION
				"No signal in IN6 input"
		::= { ded2008c01v1Entry 99 }

		-- 1.3.6.1.4.1.10106.3.101291.1.1.100
		ded2008c01v1In6AudFailTrapEnable OBJECT-TYPE
			SYNTAX AlarmEnable
			MAX-ACCESS read-write
			STATUS current
			DESCRIPTION
				"No signal in IN6 input Trap Enable"
		::= { ded2008c01v1Entry 100 }

		-- 1.3.6.1.4.1.10106.3.101291.1.1.101
		ded2008c01v1In7AudFail OBJECT-TYPE
			SYNTAX BitFail
			MAX-ACCESS read-only
			STATUS current
			DESCRIPTION
				"No signal in IN7 input"
		::= { ded2008c01v1Entry 101 }

		-- 1.3.6.1.4.1.10106.3.101291.1.1.102
		ded2008c01v1In7AudFailTrapEnable OBJECT-TYPE
			SYNTAX AlarmEnable
			MAX-ACCESS read-write
			STATUS current
			DESCRIPTION
				"No signal in IN7 input Trap Enable"
		::= { ded2008c01v1Entry 102 }

		-- 1.3.6.1.4.1.10106.3.101291.1.1.103
		ded2008c01v1In8AudFail OBJECT-TYPE
			SYNTAX BitFail
			MAX-ACCESS read-only
			STATUS current
			DESCRIPTION
				"No signal in IN8 input"
		::= { ded2008c01v1Entry 103 }

		-- 1.3.6.1.4.1.10106.3.101291.1.1.104
		ded2008c01v1In8AudFailTrapEnable OBJECT-TYPE
			SYNTAX AlarmEnable
			MAX-ACCESS read-write
			STATUS current
			DESCRIPTION
				"No signal in IN8 input Trap Enable"
		::= { ded2008c01v1Entry 104 }

		-- 1.3.6.1.4.1.10106.3.101291.1.1.105
		ded2008c01v1In1FreqFail OBJECT-TYPE
			SYNTAX BitFail
			MAX-ACCESS read-only
			STATUS current
			DESCRIPTION
				"IN1 not locked to SDI output"
		::= { ded2008c01v1Entry 105 }

		-- 1.3.6.1.4.1.10106.3.101291.1.1.107
		ded2008c01v1In2FreqFail OBJECT-TYPE
			SYNTAX BitFail
			MAX-ACCESS read-only
			STATUS current
			DESCRIPTION
				"IN2 not locked to SDI output"
		::= { ded2008c01v1Entry 107 }

		-- 1.3.6.1.4.1.10106.3.101291.1.1.109
		ded2008c01v1In3FreqFail OBJECT-TYPE
			SYNTAX BitFail
			MAX-ACCESS read-only
			STATUS current
			DESCRIPTION
				"IN3 not locked to SDI output"
		::= { ded2008c01v1Entry 109 }

		-- 1.3.6.1.4.1.10106.3.101291.1.1.111
		ded2008c01v1In4FreqFail OBJECT-TYPE
			SYNTAX BitFail
			MAX-ACCESS read-only
			STATUS current
			DESCRIPTION
				"IN4 not locked to SDI output"
		::= { ded2008c01v1Entry 111 }

		-- 1.3.6.1.4.1.10106.3.101291.1.1.113
		ded2008c01v1In5FreqFail OBJECT-TYPE
			SYNTAX BitFail
			MAX-ACCESS read-only
			STATUS current
			DESCRIPTION
				"IN5 not locked to SDI output"
		::= { ded2008c01v1Entry 113 }

		-- 1.3.6.1.4.1.10106.3.101291.1.1.115
		ded2008c01v1In6FreqFail OBJECT-TYPE
			SYNTAX BitFail
			MAX-ACCESS read-only
			STATUS current
			DESCRIPTION
				"IN6 not locked to SDI output"
		::= { ded2008c01v1Entry 115 }

		-- 1.3.6.1.4.1.10106.3.101291.1.1.117
		ded2008c01v1In7FreqFail OBJECT-TYPE
			SYNTAX BitFail
			MAX-ACCESS read-only
			STATUS current
			DESCRIPTION
				"IN7 not locked to SDI output"
		::= { ded2008c01v1Entry 117 }

		-- 1.3.6.1.4.1.10106.3.101291.1.1.119
		ded2008c01v1In8FreqFail OBJECT-TYPE
			SYNTAX BitFail
			MAX-ACCESS read-only
			STATUS current
			DESCRIPTION
				"IN8 not locked to SDI output"
		::= { ded2008c01v1Entry 119 }

		-- 1.3.6.1.4.1.10106.3.101291.1.1.121
		ded2008c01v1SdiInFmt OBJECT-TYPE
			SYNTAX Bit05251625
			MAX-ACCESS read-only
			STATUS current
			DESCRIPTION
				"Indicates the SDI input format"
		::= { ded2008c01v1Entry 121 }

		-- 1.3.6.1.4.1.10106.3.101291.1.1.123
		ded2008c01v1SerialNo OBJECT-TYPE
			SYNTAX SerialNo
			MAX-ACCESS read-only
			STATUS current
			DESCRIPTION
				"Serial number"
		::= { ded2008c01v1Entry 123 }

		-- 1.3.6.1.4.1.10106.3.600801
		uvd2000c01v1 OBJECT IDENTIFIER ::= { albalaProducts 600801 }

		-- 1.3.6.1.4.1.10106.3.600801.1
		uvd2000c01v1Table  OBJECT-TYPE
			SYNTAX SEQUENCE OF Uvd2000c01v1Entry
			MAX-ACCESS not-accessible
			STATUS current
			DESCRIPTION
				"Module  UVD2000C01V1 Table"
			::= { uvd2000c01v1 1 }

		-- 1.3.6.1.4.1.10106.3.600801.1.1
		uvd2000c01v1Entry  OBJECT-TYPE
			SYNTAX Uvd2000c01v1Entry
			MAX-ACCESS not-accessible
			STATUS current
			DESCRIPTION
				"Module UVD2000C01V1 Entry"
			INDEX { uvd2000c01v1Index }
			::= { uvd2000c01v1Table 1 }

			Uvd2000c01v1Entry ::=
			SEQUENCE {
				uvd2000c01v1Index
				ModuleIndex,
				uvd2000c01v1Input
				UvdInput,
				uvd2000c01v1InputTrapEnable
				AlarmEnable,
				uvd2000c01v1BckTxEn
				Bit0Dis1Ena,
				uvd2000c01v1Los
				BitFail,
				uvd2000c01v1LosTrapEnable
				AlarmEnable,
				uvd2000c01v1Unlock
				BitFail,
				uvd2000c01v1UnlockTrapEnable
				AlarmEnable,
				uvd2000c01v1Rate
				UopRate,
				uvd2000c01v1RateTrapEnable
				AlarmEnable,
				uvd2000c01v1SerialNo
				SerialNo
			 }

		-- 1.3.6.1.4.1.10106.3.101291.1.1.1
		uvd2000c01v1Index OBJECT-TYPE
			SYNTAX ModuleIndex
			MAX-ACCESS read-only
			STATUS current
			DESCRIPTION
				"Index of UVD2000C01V1 Table"
		::= { uvd2000c01v1Entry 1 }

		-- 1.3.6.1.4.1.10106.3.101291.1.1.3
		uvd2000c01v1Input OBJECT-TYPE
			SYNTAX UvdInput
			MAX-ACCESS read-write
			STATUS current
			DESCRIPTION
				"Indicates the input selected"
		::= { uvd2000c01v1Entry 3 }

		-- 1.3.6.1.4.1.10106.3.101291.1.1.4
		uvd2000c01v1InputTrapEnable OBJECT-TYPE
			SYNTAX AlarmEnable
			MAX-ACCESS read-write
			STATUS current
			DESCRIPTION
				"Indicates the input selected Trap Enable"
		::= { uvd2000c01v1Entry 4 }

		-- 1.3.6.1.4.1.10106.3.101291.1.1.5
		uvd2000c01v1BckTxEn OBJECT-TYPE
			SYNTAX Bit0Dis1Ena
			MAX-ACCESS read-write
			STATUS current
			DESCRIPTION
				"Enables the driver that transmit to backplane"
		::= { uvd2000c01v1Entry 5 }

		-- 1.3.6.1.4.1.10106.3.101291.1.1.7
		uvd2000c01v1Los OBJECT-TYPE
			SYNTAX BitFail
			MAX-ACCESS read-only
			STATUS current
			DESCRIPTION
				"Indicates a loss of signal"
		::= { uvd2000c01v1Entry 7 }

		-- 1.3.6.1.4.1.10106.3.101291.1.1.8
		uvd2000c01v1LosTrapEnable OBJECT-TYPE
			SYNTAX AlarmEnable
			MAX-ACCESS read-write
			STATUS current
			DESCRIPTION
				"Indicates a loss of signal Trap Enable"
		::= { uvd2000c01v1Entry 8 }

		-- 1.3.6.1.4.1.10106.3.101291.1.1.9
		uvd2000c01v1Unlock OBJECT-TYPE
			SYNTAX BitFail
			MAX-ACCESS read-only
			STATUS current
			DESCRIPTION
				"Indicates signal unlock fail"
		::= { uvd2000c01v1Entry 9 }

		-- 1.3.6.1.4.1.10106.3.101291.1.1.10
		uvd2000c01v1UnlockTrapEnable OBJECT-TYPE
			SYNTAX AlarmEnable
			MAX-ACCESS read-write
			STATUS current
			DESCRIPTION
				"Indicates signal unlock fail Trap Enable"
		::= { uvd2000c01v1Entry 10 }

		-- 1.3.6.1.4.1.10106.3.101291.1.1.11
		uvd2000c01v1Rate OBJECT-TYPE
			SYNTAX UopRate
			MAX-ACCESS read-only
			STATUS current
			DESCRIPTION
				"Indicates the SDI signal type"
		::= { uvd2000c01v1Entry 11 }

		-- 1.3.6.1.4.1.10106.3.101291.1.1.12
		uvd2000c01v1RateTrapEnable OBJECT-TYPE
			SYNTAX AlarmEnable
			MAX-ACCESS read-write
			STATUS current
			DESCRIPTION
				"Indicates the SDI signal type Trap Enable"
		::= { uvd2000c01v1Entry 12 }

		-- 1.3.6.1.4.1.10106.3.101291.1.1.13
		uvd2000c01v1SerialNo OBJECT-TYPE
			SYNTAX SerialNo
			MAX-ACCESS read-only
			STATUS current
			DESCRIPTION
				"Serial number"
		::= { uvd2000c01v1Entry 13 }

		-- 1.3.6.1.4.1.10106.3.607801
		deb2008c01v1 OBJECT IDENTIFIER ::= { albalaProducts 607801 }

		-- 1.3.6.1.4.1.10106.3.607801.1
		deb2008c01v1Table  OBJECT-TYPE
			SYNTAX SEQUENCE OF Deb2008c01v1Entry
			MAX-ACCESS not-accessible
			STATUS current
			DESCRIPTION
				"Module  DEB2008C01V1 Table"
			::= { deb2008c01v1 1 }

		-- 1.3.6.1.4.1.10106.3.607801.1.1
		deb2008c01v1Entry  OBJECT-TYPE
			SYNTAX Deb2008c01v1Entry
			MAX-ACCESS not-accessible
			STATUS current
			DESCRIPTION
				"Module DEB2008C01V1 Entry"
			INDEX { deb2008c01v1Index }
			::= { deb2008c01v1Table 1 }

			Deb2008c01v1Entry ::=
			SEQUENCE {
				deb2008c01v1Index
				ModuleIndex,
				deb2008c01v1ActivePreset
				Preset16Active,
				deb2008c01v1LoadPreset
				Preset16Load,
				deb2008c01v1SavePreset
				Preset16Save,
				deb2008c01v1ManNAuto
				Bit0Aut1Man,
				deb2008c01v1AesInNOut
				Bit0Out1In,
				deb2008c01v1BaseSlot
				Uint5,
				deb2008c01v1SlotUsedOne
				AdbDabSlot,
				deb2008c01v1SlotUsedTwo
				DdbSlots,
				deb2008c01v1OvldLevel
				LevelDbfsA,
				deb2008c01v1ChSel
				AudioChannels3,
				deb2008c01v1In1Mode
				Bit0No1Yes,
				deb2008c01v1In2Mode
				Bit0No1Yes,
				deb2008c01v1In3Mode
				Bit0No1Yes,
				deb2008c01v1In4Mode
				Bit0No1Yes,
				deb2008c01v1In5Mode
				Bit0No1Yes,
				deb2008c01v1In6Mode
				Bit0No1Yes,
				deb2008c01v1In7Mode
				Bit0No1Yes,
				deb2008c01v1In8Mode
				Bit0No1Yes,
				deb2008c01v1Out1AsrcEn
				Bit0No1Yes,
				deb2008c01v1Out2AsrcEn
				Bit0No1Yes,
				deb2008c01v1Out3AsrcEn
				Bit0No1Yes,
				deb2008c01v1Out4AsrcEn
				Bit0No1Yes,
				deb2008c01v1Gain0
				Gain24dbMute,
				deb2008c01v1Phase0
				Bit0Nor1Inv,
				deb2008c01v1Gain1
				Gain24dbMute,
				deb2008c01v1Phase1
				Bit0Nor1Inv,
				deb2008c01v1Gain2
				Gain24dbMute,
				deb2008c01v1Phase2
				Bit0Nor1Inv,
				deb2008c01v1Gain3
				Gain24dbMute,
				deb2008c01v1Phase3
				Bit0Nor1Inv,
				deb2008c01v1Gain4
				Gain24dbMute,
				deb2008c01v1Phase4
				Bit0Nor1Inv,
				deb2008c01v1Gain5
				Gain24dbMute,
				deb2008c01v1Phase5
				Bit0Nor1Inv,
				deb2008c01v1Gain6
				Gain24dbMute,
				deb2008c01v1Phase6
				Bit0Nor1Inv,
				deb2008c01v1Gain7
				Gain24dbMute,
				deb2008c01v1Phase7
				Bit0Nor1Inv,
				deb2008c01v1Gain8
				Gain24dbMute,
				deb2008c01v1Phase8
				Bit0Nor1Inv,
				deb2008c01v1Gain9
				Gain24dbMute,
				deb2008c01v1Phase9
				Bit0Nor1Inv,
				deb2008c01v1Gain10
				Gain24dbMute,
				deb2008c01v1Phase10
				Bit0Nor1Inv,
				deb2008c01v1Gain11
				Gain24dbMute,
				deb2008c01v1Phase11
				Bit0Nor1Inv,
				deb2008c01v1Gain12
				Gain24dbMute,
				deb2008c01v1Phase12
				Bit0Nor1Inv,
				deb2008c01v1Gain13
				Gain24dbMute,
				deb2008c01v1Phase13
				Bit0Nor1Inv,
				deb2008c01v1Gain14
				Gain24dbMute,
				deb2008c01v1Phase14
				Bit0Nor1Inv,
				deb2008c01v1Gain15
				Gain24dbMute,
				deb2008c01v1Phase15
				Bit0Nor1Inv,
				deb2008c01v1BusTimFail
				BitFail,
				deb2008c01v1BusTimUnlck
				BitFail,
				deb2008c01v1BusAudFail
				BitFail,
				deb2008c01v1BusAudError
				BitFail,
				deb2008c01v1AudClipEr
				BitFail,
				deb2008c01v1AudClipErTrapEnable
				AlarmEnable,
				deb2008c01v1AudPresFail
				BitFail,
				deb2008c01v1AudPresFailTrapEnable
				AlarmEnable,
				deb2008c01v1AudInsFail
				BitFail,
				deb2008c01v1AudInsFailTrapEnable
				AlarmEnable,
				deb2008c01v1AudOvldEr
				BitFail,
				deb2008c01v1AudOvldErTrapEnable
				AlarmEnable,
				deb2008c01v1Slot1Pres
				Bit0No1Yes,
				deb2008c01v1Slot2Pres
				Bit0No1Yes,
				deb2008c01v1Slot3Pres
				Bit0No1Yes,
				deb2008c01v1Slot4Pres
				Bit0No1Yes,
				deb2008c01v1Slot5Pres
				Bit0No1Yes,
				deb2008c01v1Slot6Pres
				Bit0No1Yes,
				deb2008c01v1Slot7Pres
				Bit0No1Yes,
				deb2008c01v1Slot8Pres
				Bit0No1Yes,
				deb2008c01v1Aes1Pres
				Bit0No1Yes,
				deb2008c01v1Aes1RefPres
				Bit0No1Yes,
				deb2008c01v1Aes2Pres
				Bit0No1Yes,
				deb2008c01v1Aes2RefPres
				Bit0No1Yes,
				deb2008c01v1Aes3Pres
				Bit0No1Yes,
				deb2008c01v1Aes3RefPres
				Bit0No1Yes,
				deb2008c01v1Aes4Pres
				Bit0No1Yes,
				deb2008c01v1Aes4RefPres
				Bit0No1Yes,
				deb2008c01v1Aes5Pres
				Bit0No1Yes,
				deb2008c01v1Aes6Pres
				Bit0No1Yes,
				deb2008c01v1Aes7Pres
				Bit0No1Yes,
				deb2008c01v1Aes8Pres
				Bit0No1Yes,
				deb2008c01v1Aes1AsyncFail
				BitFail,
				deb2008c01v1Aes2AsyncFail
				BitFail,
				deb2008c01v1Aes3AsyncFail
				BitFail,
				deb2008c01v1Aes4AsyncFail
				BitFail,
				deb2008c01v1Aes5AsyncFail
				BitFail,
				deb2008c01v1Aes6AsyncFail
				BitFail,
				deb2008c01v1Aes7AsyncFail
				BitFail,
				deb2008c01v1Aes8AsyncFail
				BitFail,
				deb2008c01v1AsrcRefFail
				BitFail,
				deb2008c01v1SerialNo
				SerialNo
			 }

		-- 1.3.6.1.4.1.10106.3.101291.1.1.1
		deb2008c01v1Index OBJECT-TYPE
			SYNTAX ModuleIndex
			MAX-ACCESS read-only
			STATUS current
			DESCRIPTION
				"Index of DEB2008C01V1 Table"
		::= { deb2008c01v1Entry 1 }

		-- 1.3.6.1.4.1.10106.3.101291.1.1.3
		deb2008c01v1ActivePreset OBJECT-TYPE
			SYNTAX Preset16Active
			MAX-ACCESS read-only
			STATUS current
			DESCRIPTION
				"Shows the active preset"
		::= { deb2008c01v1Entry 3 }

		-- 1.3.6.1.4.1.10106.3.101291.1.1.5
		deb2008c01v1LoadPreset OBJECT-TYPE
			SYNTAX Preset16Load
			MAX-ACCESS read-write
			STATUS current
			DESCRIPTION
				"Allows loading a preset"
		::= { deb2008c01v1Entry 5 }

		-- 1.3.6.1.4.1.10106.3.101291.1.1.7
		deb2008c01v1SavePreset OBJECT-TYPE
			SYNTAX Preset16Save
			MAX-ACCESS read-write
			STATUS current
			DESCRIPTION
				"Allows saving a preset"
		::= { deb2008c01v1Entry 7 }

		-- 1.3.6.1.4.1.10106.3.101291.1.1.9
		deb2008c01v1ManNAuto OBJECT-TYPE
			SYNTAX Bit0Aut1Man
			MAX-ACCESS read-write
			STATUS current
			DESCRIPTION
				"It allows selecting the slot working mode"
		::= { deb2008c01v1Entry 9 }

		-- 1.3.6.1.4.1.10106.3.101291.1.1.11
		deb2008c01v1AesInNOut OBJECT-TYPE
			SYNTAX Bit0Out1In
			MAX-ACCESS read-write
			STATUS current
			DESCRIPTION
				"It allows selecting whether the AES signals are inputs or outputs"
		::= { deb2008c01v1Entry 11 }

		-- 1.3.6.1.4.1.10106.3.101291.1.1.13
		deb2008c01v1BaseSlot OBJECT-TYPE
			SYNTAX Uint5
			MAX-ACCESS read-write
			STATUS current
			DESCRIPTION
				"Base rack slot"
		::= { deb2008c01v1Entry 13 }

		-- 1.3.6.1.4.1.10106.3.101291.1.1.15
		deb2008c01v1SlotUsedOne OBJECT-TYPE
			SYNTAX AdbDabSlot
			MAX-ACCESS read-write
			STATUS current
			DESCRIPTION
				"Employed slot"
		::= { deb2008c01v1Entry 15 }

		-- 1.3.6.1.4.1.10106.3.101291.1.1.17
		deb2008c01v1SlotUsedTwo OBJECT-TYPE
			SYNTAX DdbSlots
			MAX-ACCESS read-write
			STATUS current
			DESCRIPTION
				"Employed slots"
		::= { deb2008c01v1Entry 17 }

		-- 1.3.6.1.4.1.10106.3.101291.1.1.19
		deb2008c01v1OvldLevel OBJECT-TYPE
			SYNTAX LevelDbfsA
			MAX-ACCESS read-write
			STATUS current
			DESCRIPTION
				"It allows selecting the overload audio level"
		::= { deb2008c01v1Entry 19 }

		-- 1.3.6.1.4.1.10106.3.101291.1.1.21
		deb2008c01v1ChSel OBJECT-TYPE
			SYNTAX AudioChannels3
			MAX-ACCESS read-write
			STATUS current
			DESCRIPTION
				"Selects how many audio channels will be processed"
		::= { deb2008c01v1Entry 21 }

		-- 1.3.6.1.4.1.10106.3.101291.1.1.23
		deb2008c01v1In1Mode OBJECT-TYPE
			SYNTAX Bit0No1Yes
			MAX-ACCESS read-write
			STATUS current
			DESCRIPTION
				"Enable ASRC in AES1 input"
		::= { deb2008c01v1Entry 23 }

		-- 1.3.6.1.4.1.10106.3.101291.1.1.25
		deb2008c01v1In2Mode OBJECT-TYPE
			SYNTAX Bit0No1Yes
			MAX-ACCESS read-write
			STATUS current
			DESCRIPTION
				"Enable ASRC in AES2 input"
		::= { deb2008c01v1Entry 25 }

		-- 1.3.6.1.4.1.10106.3.101291.1.1.27
		deb2008c01v1In3Mode OBJECT-TYPE
			SYNTAX Bit0No1Yes
			MAX-ACCESS read-write
			STATUS current
			DESCRIPTION
				"Enable ASRC in AES3 input"
		::= { deb2008c01v1Entry 27 }

		-- 1.3.6.1.4.1.10106.3.101291.1.1.29
		deb2008c01v1In4Mode OBJECT-TYPE
			SYNTAX Bit0No1Yes
			MAX-ACCESS read-write
			STATUS current
			DESCRIPTION
				"Enable ASRC in AES4 input"
		::= { deb2008c01v1Entry 29 }

		-- 1.3.6.1.4.1.10106.3.101291.1.1.31
		deb2008c01v1In5Mode OBJECT-TYPE
			SYNTAX Bit0No1Yes
			MAX-ACCESS read-write
			STATUS current
			DESCRIPTION
				"Enable ASRC in AES5 input"
		::= { deb2008c01v1Entry 31 }

		-- 1.3.6.1.4.1.10106.3.101291.1.1.33
		deb2008c01v1In6Mode OBJECT-TYPE
			SYNTAX Bit0No1Yes
			MAX-ACCESS read-write
			STATUS current
			DESCRIPTION
				"Enable ASRC in AES6 input"
		::= { deb2008c01v1Entry 33 }

		-- 1.3.6.1.4.1.10106.3.101291.1.1.35
		deb2008c01v1In7Mode OBJECT-TYPE
			SYNTAX Bit0No1Yes
			MAX-ACCESS read-write
			STATUS current
			DESCRIPTION
				"Enable ASRC in AES7 input"
		::= { deb2008c01v1Entry 35 }

		-- 1.3.6.1.4.1.10106.3.101291.1.1.37
		deb2008c01v1In8Mode OBJECT-TYPE
			SYNTAX Bit0No1Yes
			MAX-ACCESS read-write
			STATUS current
			DESCRIPTION
				"Enable ASRC in AES8 input"
		::= { deb2008c01v1Entry 37 }

		-- 1.3.6.1.4.1.10106.3.101291.1.1.39
		deb2008c01v1Out1AsrcEn OBJECT-TYPE
			SYNTAX Bit0No1Yes
			MAX-ACCESS read-write
			STATUS current
			DESCRIPTION
				"Enables ASRC in AES1 output"
		::= { deb2008c01v1Entry 39 }

		-- 1.3.6.1.4.1.10106.3.101291.1.1.41
		deb2008c01v1Out2AsrcEn OBJECT-TYPE
			SYNTAX Bit0No1Yes
			MAX-ACCESS read-write
			STATUS current
			DESCRIPTION
				"Enables ASRC in AES2 output"
		::= { deb2008c01v1Entry 41 }

		-- 1.3.6.1.4.1.10106.3.101291.1.1.43
		deb2008c01v1Out3AsrcEn OBJECT-TYPE
			SYNTAX Bit0No1Yes
			MAX-ACCESS read-write
			STATUS current
			DESCRIPTION
				"Enables ASRC in AES3 output"
		::= { deb2008c01v1Entry 43 }

		-- 1.3.6.1.4.1.10106.3.101291.1.1.45
		deb2008c01v1Out4AsrcEn OBJECT-TYPE
			SYNTAX Bit0No1Yes
			MAX-ACCESS read-write
			STATUS current
			DESCRIPTION
				"Enables ASRC in AES4 output"
		::= { deb2008c01v1Entry 45 }

		-- 1.3.6.1.4.1.10106.3.101291.1.1.47
		deb2008c01v1Gain0 OBJECT-TYPE
			SYNTAX Gain24dbMute
			MAX-ACCESS read-write
			STATUS current
			DESCRIPTION
				"Gain applied to the left channel of AES1"
		::= { deb2008c01v1Entry 47 }

		-- 1.3.6.1.4.1.10106.3.101291.1.1.49
		deb2008c01v1Phase0 OBJECT-TYPE
			SYNTAX Bit0Nor1Inv
			MAX-ACCESS read-write
			STATUS current
			DESCRIPTION
				"Phase gain applied to the left channel of AES1"
		::= { deb2008c01v1Entry 49 }

		-- 1.3.6.1.4.1.10106.3.101291.1.1.51
		deb2008c01v1Gain1 OBJECT-TYPE
			SYNTAX Gain24dbMute
			MAX-ACCESS read-write
			STATUS current
			DESCRIPTION
				"Gain applied to the right channel of AES1"
		::= { deb2008c01v1Entry 51 }

		-- 1.3.6.1.4.1.10106.3.101291.1.1.53
		deb2008c01v1Phase1 OBJECT-TYPE
			SYNTAX Bit0Nor1Inv
			MAX-ACCESS read-write
			STATUS current
			DESCRIPTION
				"Phase gain applied to the right channel of AES1"
		::= { deb2008c01v1Entry 53 }

		-- 1.3.6.1.4.1.10106.3.101291.1.1.55
		deb2008c01v1Gain2 OBJECT-TYPE
			SYNTAX Gain24dbMute
			MAX-ACCESS read-write
			STATUS current
			DESCRIPTION
				"Gain applied to the left channel of AES2"
		::= { deb2008c01v1Entry 55 }

		-- 1.3.6.1.4.1.10106.3.101291.1.1.57
		deb2008c01v1Phase2 OBJECT-TYPE
			SYNTAX Bit0Nor1Inv
			MAX-ACCESS read-write
			STATUS current
			DESCRIPTION
				"Phase gain applied to the left channel of AES2"
		::= { deb2008c01v1Entry 57 }

		-- 1.3.6.1.4.1.10106.3.101291.1.1.59
		deb2008c01v1Gain3 OBJECT-TYPE
			SYNTAX Gain24dbMute
			MAX-ACCESS read-write
			STATUS current
			DESCRIPTION
				"Gain applied to the right channel of AES2"
		::= { deb2008c01v1Entry 59 }

		-- 1.3.6.1.4.1.10106.3.101291.1.1.61
		deb2008c01v1Phase3 OBJECT-TYPE
			SYNTAX Bit0Nor1Inv
			MAX-ACCESS read-write
			STATUS current
			DESCRIPTION
				"Phase gain applied to the right channel of AES2"
		::= { deb2008c01v1Entry 61 }

		-- 1.3.6.1.4.1.10106.3.101291.1.1.63
		deb2008c01v1Gain4 OBJECT-TYPE
			SYNTAX Gain24dbMute
			MAX-ACCESS read-write
			STATUS current
			DESCRIPTION
				"Gain applied to the left channel of AES3"
		::= { deb2008c01v1Entry 63 }

		-- 1.3.6.1.4.1.10106.3.101291.1.1.65
		deb2008c01v1Phase4 OBJECT-TYPE
			SYNTAX Bit0Nor1Inv
			MAX-ACCESS read-write
			STATUS current
			DESCRIPTION
				"Phase gain applied to the left channel of AES3"
		::= { deb2008c01v1Entry 65 }

		-- 1.3.6.1.4.1.10106.3.101291.1.1.67
		deb2008c01v1Gain5 OBJECT-TYPE
			SYNTAX Gain24dbMute
			MAX-ACCESS read-write
			STATUS current
			DESCRIPTION
				"Gain applied to the right channel of AES3"
		::= { deb2008c01v1Entry 67 }

		-- 1.3.6.1.4.1.10106.3.101291.1.1.69
		deb2008c01v1Phase5 OBJECT-TYPE
			SYNTAX Bit0Nor1Inv
			MAX-ACCESS read-write
			STATUS current
			DESCRIPTION
				"Phase gain applied to the right channel of AES3"
		::= { deb2008c01v1Entry 69 }

		-- 1.3.6.1.4.1.10106.3.101291.1.1.71
		deb2008c01v1Gain6 OBJECT-TYPE
			SYNTAX Gain24dbMute
			MAX-ACCESS read-write
			STATUS current
			DESCRIPTION
				"Gain applied to the left channel of AES4"
		::= { deb2008c01v1Entry 71 }

		-- 1.3.6.1.4.1.10106.3.101291.1.1.73
		deb2008c01v1Phase6 OBJECT-TYPE
			SYNTAX Bit0Nor1Inv
			MAX-ACCESS read-write
			STATUS current
			DESCRIPTION
				"Phase gain applied to the left channel of AES4"
		::= { deb2008c01v1Entry 73 }

		-- 1.3.6.1.4.1.10106.3.101291.1.1.75
		deb2008c01v1Gain7 OBJECT-TYPE
			SYNTAX Gain24dbMute
			MAX-ACCESS read-write
			STATUS current
			DESCRIPTION
				"Gain applied to the right channel of AES4"
		::= { deb2008c01v1Entry 75 }

		-- 1.3.6.1.4.1.10106.3.101291.1.1.77
		deb2008c01v1Phase7 OBJECT-TYPE
			SYNTAX Bit0Nor1Inv
			MAX-ACCESS read-write
			STATUS current
			DESCRIPTION
				"Phase gain applied to the right channel of AES4"
		::= { deb2008c01v1Entry 77 }

		-- 1.3.6.1.4.1.10106.3.101291.1.1.79
		deb2008c01v1Gain8 OBJECT-TYPE
			SYNTAX Gain24dbMute
			MAX-ACCESS read-write
			STATUS current
			DESCRIPTION
				"Gain applied to the left channel of AES5"
		::= { deb2008c01v1Entry 79 }

		-- 1.3.6.1.4.1.10106.3.101291.1.1.81
		deb2008c01v1Phase8 OBJECT-TYPE
			SYNTAX Bit0Nor1Inv
			MAX-ACCESS read-write
			STATUS current
			DESCRIPTION
				"Phase gain applied to the left channel of AES5"
		::= { deb2008c01v1Entry 81 }

		-- 1.3.6.1.4.1.10106.3.101291.1.1.83
		deb2008c01v1Gain9 OBJECT-TYPE
			SYNTAX Gain24dbMute
			MAX-ACCESS read-write
			STATUS current
			DESCRIPTION
				"Gain applied to the right channel of AES5"
		::= { deb2008c01v1Entry 83 }

		-- 1.3.6.1.4.1.10106.3.101291.1.1.85
		deb2008c01v1Phase9 OBJECT-TYPE
			SYNTAX Bit0Nor1Inv
			MAX-ACCESS read-write
			STATUS current
			DESCRIPTION
				"Phase gain applied to the right channel of AES5"
		::= { deb2008c01v1Entry 85 }

		-- 1.3.6.1.4.1.10106.3.101291.1.1.87
		deb2008c01v1Gain10 OBJECT-TYPE
			SYNTAX Gain24dbMute
			MAX-ACCESS read-write
			STATUS current
			DESCRIPTION
				"Gain applied to the left channel of AES6"
		::= { deb2008c01v1Entry 87 }

		-- 1.3.6.1.4.1.10106.3.101291.1.1.89
		deb2008c01v1Phase10 OBJECT-TYPE
			SYNTAX Bit0Nor1Inv
			MAX-ACCESS read-write
			STATUS current
			DESCRIPTION
				"Phase gain applied to the left channel of AES6"
		::= { deb2008c01v1Entry 89 }

		-- 1.3.6.1.4.1.10106.3.101291.1.1.91
		deb2008c01v1Gain11 OBJECT-TYPE
			SYNTAX Gain24dbMute
			MAX-ACCESS read-write
			STATUS current
			DESCRIPTION
				"Gain applied to the right channel of AES6"
		::= { deb2008c01v1Entry 91 }

		-- 1.3.6.1.4.1.10106.3.101291.1.1.93
		deb2008c01v1Phase11 OBJECT-TYPE
			SYNTAX Bit0Nor1Inv
			MAX-ACCESS read-write
			STATUS current
			DESCRIPTION
				"Phase gain applied to the right channel of AES6"
		::= { deb2008c01v1Entry 93 }

		-- 1.3.6.1.4.1.10106.3.101291.1.1.95
		deb2008c01v1Gain12 OBJECT-TYPE
			SYNTAX Gain24dbMute
			MAX-ACCESS read-write
			STATUS current
			DESCRIPTION
				"Gain applied to the left channel of AES7"
		::= { deb2008c01v1Entry 95 }

		-- 1.3.6.1.4.1.10106.3.101291.1.1.97
		deb2008c01v1Phase12 OBJECT-TYPE
			SYNTAX Bit0Nor1Inv
			MAX-ACCESS read-write
			STATUS current
			DESCRIPTION
				"Phase gain applied to the left channel of AES7"
		::= { deb2008c01v1Entry 97 }

		-- 1.3.6.1.4.1.10106.3.101291.1.1.99
		deb2008c01v1Gain13 OBJECT-TYPE
			SYNTAX Gain24dbMute
			MAX-ACCESS read-write
			STATUS current
			DESCRIPTION
				"Gain applied to the right channel of AES7"
		::= { deb2008c01v1Entry 99 }

		-- 1.3.6.1.4.1.10106.3.101291.1.1.101
		deb2008c01v1Phase13 OBJECT-TYPE
			SYNTAX Bit0Nor1Inv
			MAX-ACCESS read-write
			STATUS current
			DESCRIPTION
				"Phase gain applied to the right channel of AES7"
		::= { deb2008c01v1Entry 101 }

		-- 1.3.6.1.4.1.10106.3.101291.1.1.103
		deb2008c01v1Gain14 OBJECT-TYPE
			SYNTAX Gain24dbMute
			MAX-ACCESS read-write
			STATUS current
			DESCRIPTION
				"Gain applied to the left channel of AES8"
		::= { deb2008c01v1Entry 103 }

		-- 1.3.6.1.4.1.10106.3.101291.1.1.105
		deb2008c01v1Phase14 OBJECT-TYPE
			SYNTAX Bit0Nor1Inv
			MAX-ACCESS read-write
			STATUS current
			DESCRIPTION
				"Phase gain applied to the left channel of AES8"
		::= { deb2008c01v1Entry 105 }

		-- 1.3.6.1.4.1.10106.3.101291.1.1.107
		deb2008c01v1Gain15 OBJECT-TYPE
			SYNTAX Gain24dbMute
			MAX-ACCESS read-write
			STATUS current
			DESCRIPTION
				"Gain applied to the right channel of AES8"
		::= { deb2008c01v1Entry 107 }

		-- 1.3.6.1.4.1.10106.3.101291.1.1.109
		deb2008c01v1Phase15 OBJECT-TYPE
			SYNTAX Bit0Nor1Inv
			MAX-ACCESS read-write
			STATUS current
			DESCRIPTION
				"Phase gain applied to the right channel of AES8"
		::= { deb2008c01v1Entry 109 }

		-- 1.3.6.1.4.1.10106.3.101291.1.1.111
		deb2008c01v1BusTimFail OBJECT-TYPE
			SYNTAX BitFail
			MAX-ACCESS read-only
			STATUS current
			DESCRIPTION
				"Synchronization internal rack bus fail"
		::= { deb2008c01v1Entry 111 }

		-- 1.3.6.1.4.1.10106.3.101291.1.1.113
		deb2008c01v1BusTimUnlck OBJECT-TYPE
			SYNTAX BitFail
			MAX-ACCESS read-only
			STATUS current
			DESCRIPTION
				"Synchronization internal rack bus unlocked"
		::= { deb2008c01v1Entry 113 }

		-- 1.3.6.1.4.1.10106.3.101291.1.1.115
		deb2008c01v1BusAudFail OBJECT-TYPE
			SYNTAX BitFail
			MAX-ACCESS read-only
			STATUS current
			DESCRIPTION
				"Audio bus signal not present in rack"
		::= { deb2008c01v1Entry 115 }

		-- 1.3.6.1.4.1.10106.3.101291.1.1.117
		deb2008c01v1BusAudError OBJECT-TYPE
			SYNTAX BitFail
			MAX-ACCESS read-only
			STATUS current
			DESCRIPTION
				"Audio bus signal contains errors"
		::= { deb2008c01v1Entry 117 }

		-- 1.3.6.1.4.1.10106.3.101291.1.1.119
		deb2008c01v1AudClipEr OBJECT-TYPE
			SYNTAX BitFail
			MAX-ACCESS read-only
			STATUS current
			DESCRIPTION
				"Audio clipping error"
		::= { deb2008c01v1Entry 119 }

		-- 1.3.6.1.4.1.10106.3.101291.1.1.120
		deb2008c01v1AudClipErTrapEnable OBJECT-TYPE
			SYNTAX AlarmEnable
			MAX-ACCESS read-write
			STATUS current
			DESCRIPTION
				"Audio clipping error Trap Enable"
		::= { deb2008c01v1Entry 120 }

		-- 1.3.6.1.4.1.10106.3.101291.1.1.121
		deb2008c01v1AudPresFail OBJECT-TYPE
			SYNTAX BitFail
			MAX-ACCESS read-only
			STATUS current
			DESCRIPTION
				"It lights up when the backplane bus does not have all the audio channels the module is required to read"
		::= { deb2008c01v1Entry 121 }

		-- 1.3.6.1.4.1.10106.3.101291.1.1.122
		deb2008c01v1AudPresFailTrapEnable OBJECT-TYPE
			SYNTAX AlarmEnable
			MAX-ACCESS read-write
			STATUS current
			DESCRIPTION
				"It lights up when the backplane bus does not have all the audio channels the module is required to read Trap Enable"
		::= { deb2008c01v1Entry 122 }

		-- 1.3.6.1.4.1.10106.3.101291.1.1.123
		deb2008c01v1AudInsFail OBJECT-TYPE
			SYNTAX BitFail
			MAX-ACCESS read-only
			STATUS current
			DESCRIPTION
				"It lights up when the module cannot insert in the backplane bus the audio channels"
		::= { deb2008c01v1Entry 123 }

		-- 1.3.6.1.4.1.10106.3.101291.1.1.124
		deb2008c01v1AudInsFailTrapEnable OBJECT-TYPE
			SYNTAX AlarmEnable
			MAX-ACCESS read-write
			STATUS current
			DESCRIPTION
				"It lights up when the module cannot insert in the backplane bus the audio channels Trap Enable"
		::= { deb2008c01v1Entry 124 }

		-- 1.3.6.1.4.1.10106.3.101291.1.1.125
		deb2008c01v1AudOvldEr OBJECT-TYPE
			SYNTAX BitFail
			MAX-ACCESS read-only
			STATUS current
			DESCRIPTION
				"Audio overload fail"
		::= { deb2008c01v1Entry 125 }

		-- 1.3.6.1.4.1.10106.3.101291.1.1.126
		deb2008c01v1AudOvldErTrapEnable OBJECT-TYPE
			SYNTAX AlarmEnable
			MAX-ACCESS read-write
			STATUS current
			DESCRIPTION
				"Audio overload fail Trap Enable"
		::= { deb2008c01v1Entry 126 }

		-- 1.3.6.1.4.1.10106.3.101291.1.1.127
		deb2008c01v1Slot1Pres OBJECT-TYPE
			SYNTAX Bit0No1Yes
			MAX-ACCESS read-only
			STATUS current
			DESCRIPTION
				"Slot 1 data presence"
		::= { deb2008c01v1Entry 127 }

		-- 1.3.6.1.4.1.10106.3.101291.1.1.129
		deb2008c01v1Slot2Pres OBJECT-TYPE
			SYNTAX Bit0No1Yes
			MAX-ACCESS read-only
			STATUS current
			DESCRIPTION
				"Slot 2 data presence"
		::= { deb2008c01v1Entry 129 }

		-- 1.3.6.1.4.1.10106.3.101291.1.1.131
		deb2008c01v1Slot3Pres OBJECT-TYPE
			SYNTAX Bit0No1Yes
			MAX-ACCESS read-only
			STATUS current
			DESCRIPTION
				"Slot 3 data presence"
		::= { deb2008c01v1Entry 131 }

		-- 1.3.6.1.4.1.10106.3.101291.1.1.133
		deb2008c01v1Slot4Pres OBJECT-TYPE
			SYNTAX Bit0No1Yes
			MAX-ACCESS read-only
			STATUS current
			DESCRIPTION
				"Slot 4 data presence"
		::= { deb2008c01v1Entry 133 }

		-- 1.3.6.1.4.1.10106.3.101291.1.1.135
		deb2008c01v1Slot5Pres OBJECT-TYPE
			SYNTAX Bit0No1Yes
			MAX-ACCESS read-only
			STATUS current
			DESCRIPTION
				"Slot 5 data presence"
		::= { deb2008c01v1Entry 135 }

		-- 1.3.6.1.4.1.10106.3.101291.1.1.137
		deb2008c01v1Slot6Pres OBJECT-TYPE
			SYNTAX Bit0No1Yes
			MAX-ACCESS read-only
			STATUS current
			DESCRIPTION
				"Slot 6 data presence"
		::= { deb2008c01v1Entry 137 }

		-- 1.3.6.1.4.1.10106.3.101291.1.1.139
		deb2008c01v1Slot7Pres OBJECT-TYPE
			SYNTAX Bit0No1Yes
			MAX-ACCESS read-only
			STATUS current
			DESCRIPTION
				"Slot 7 data presence"
		::= { deb2008c01v1Entry 139 }

		-- 1.3.6.1.4.1.10106.3.101291.1.1.141
		deb2008c01v1Slot8Pres OBJECT-TYPE
			SYNTAX Bit0No1Yes
			MAX-ACCESS read-only
			STATUS current
			DESCRIPTION
				"Slot 8 data presence"
		::= { deb2008c01v1Entry 141 }

		-- 1.3.6.1.4.1.10106.3.101291.1.1.143
		deb2008c01v1Aes1Pres OBJECT-TYPE
			SYNTAX Bit0No1Yes
			MAX-ACCESS read-only
			STATUS current
			DESCRIPTION
				"AES1 presence"
		::= { deb2008c01v1Entry 143 }

		-- 1.3.6.1.4.1.10106.3.101291.1.1.145
		deb2008c01v1Aes1RefPres OBJECT-TYPE
			SYNTAX Bit0No1Yes
			MAX-ACCESS read-only
			STATUS current
			DESCRIPTION
				"AES1 reference presence"
		::= { deb2008c01v1Entry 145 }

		-- 1.3.6.1.4.1.10106.3.101291.1.1.147
		deb2008c01v1Aes2Pres OBJECT-TYPE
			SYNTAX Bit0No1Yes
			MAX-ACCESS read-only
			STATUS current
			DESCRIPTION
				"AES2 presence"
		::= { deb2008c01v1Entry 147 }

		-- 1.3.6.1.4.1.10106.3.101291.1.1.149
		deb2008c01v1Aes2RefPres OBJECT-TYPE
			SYNTAX Bit0No1Yes
			MAX-ACCESS read-only
			STATUS current
			DESCRIPTION
				"AES2 reference presence"
		::= { deb2008c01v1Entry 149 }

		-- 1.3.6.1.4.1.10106.3.101291.1.1.151
		deb2008c01v1Aes3Pres OBJECT-TYPE
			SYNTAX Bit0No1Yes
			MAX-ACCESS read-only
			STATUS current
			DESCRIPTION
				"AES3 presence"
		::= { deb2008c01v1Entry 151 }

		-- 1.3.6.1.4.1.10106.3.101291.1.1.153
		deb2008c01v1Aes3RefPres OBJECT-TYPE
			SYNTAX Bit0No1Yes
			MAX-ACCESS read-only
			STATUS current
			DESCRIPTION
				"AES3 reference presence"
		::= { deb2008c01v1Entry 153 }

		-- 1.3.6.1.4.1.10106.3.101291.1.1.155
		deb2008c01v1Aes4Pres OBJECT-TYPE
			SYNTAX Bit0No1Yes
			MAX-ACCESS read-only
			STATUS current
			DESCRIPTION
				"AES4 presence"
		::= { deb2008c01v1Entry 155 }

		-- 1.3.6.1.4.1.10106.3.101291.1.1.157
		deb2008c01v1Aes4RefPres OBJECT-TYPE
			SYNTAX Bit0No1Yes
			MAX-ACCESS read-only
			STATUS current
			DESCRIPTION
				"AES4 reference presence"
		::= { deb2008c01v1Entry 157 }

		-- 1.3.6.1.4.1.10106.3.101291.1.1.159
		deb2008c01v1Aes5Pres OBJECT-TYPE
			SYNTAX Bit0No1Yes
			MAX-ACCESS read-only
			STATUS current
			DESCRIPTION
				"AES5 presence"
		::= { deb2008c01v1Entry 159 }

		-- 1.3.6.1.4.1.10106.3.101291.1.1.161
		deb2008c01v1Aes6Pres OBJECT-TYPE
			SYNTAX Bit0No1Yes
			MAX-ACCESS read-only
			STATUS current
			DESCRIPTION
				"AES6 presence"
		::= { deb2008c01v1Entry 161 }

		-- 1.3.6.1.4.1.10106.3.101291.1.1.163
		deb2008c01v1Aes7Pres OBJECT-TYPE
			SYNTAX Bit0No1Yes
			MAX-ACCESS read-only
			STATUS current
			DESCRIPTION
				"AES7 presence"
		::= { deb2008c01v1Entry 163 }

		-- 1.3.6.1.4.1.10106.3.101291.1.1.165
		deb2008c01v1Aes8Pres OBJECT-TYPE
			SYNTAX Bit0No1Yes
			MAX-ACCESS read-only
			STATUS current
			DESCRIPTION
				"AES8 presence"
		::= { deb2008c01v1Entry 165 }

		-- 1.3.6.1.4.1.10106.3.101291.1.1.167
		deb2008c01v1Aes1AsyncFail OBJECT-TYPE
			SYNTAX BitFail
			MAX-ACCESS read-only
			STATUS current
			DESCRIPTION
				"AES1 asynchronous fail"
		::= { deb2008c01v1Entry 167 }

		-- 1.3.6.1.4.1.10106.3.101291.1.1.169
		deb2008c01v1Aes2AsyncFail OBJECT-TYPE
			SYNTAX BitFail
			MAX-ACCESS read-only
			STATUS current
			DESCRIPTION
				"AES2 asynchronous fail"
		::= { deb2008c01v1Entry 169 }

		-- 1.3.6.1.4.1.10106.3.101291.1.1.171
		deb2008c01v1Aes3AsyncFail OBJECT-TYPE
			SYNTAX BitFail
			MAX-ACCESS read-only
			STATUS current
			DESCRIPTION
				"AES3 asynchronous fail"
		::= { deb2008c01v1Entry 171 }

		-- 1.3.6.1.4.1.10106.3.101291.1.1.173
		deb2008c01v1Aes4AsyncFail OBJECT-TYPE
			SYNTAX BitFail
			MAX-ACCESS read-only
			STATUS current
			DESCRIPTION
				"AES4 asynchronous fail"
		::= { deb2008c01v1Entry 173 }

		-- 1.3.6.1.4.1.10106.3.101291.1.1.175
		deb2008c01v1Aes5AsyncFail OBJECT-TYPE
			SYNTAX BitFail
			MAX-ACCESS read-only
			STATUS current
			DESCRIPTION
				"AES5 asynchronous fail"
		::= { deb2008c01v1Entry 175 }

		-- 1.3.6.1.4.1.10106.3.101291.1.1.177
		deb2008c01v1Aes6AsyncFail OBJECT-TYPE
			SYNTAX BitFail
			MAX-ACCESS read-only
			STATUS current
			DESCRIPTION
				"AES6 asynchronous fail"
		::= { deb2008c01v1Entry 177 }

		-- 1.3.6.1.4.1.10106.3.101291.1.1.179
		deb2008c01v1Aes7AsyncFail OBJECT-TYPE
			SYNTAX BitFail
			MAX-ACCESS read-only
			STATUS current
			DESCRIPTION
				"AES7 asynchronous fail"
		::= { deb2008c01v1Entry 179 }

		-- 1.3.6.1.4.1.10106.3.101291.1.1.181
		deb2008c01v1Aes8AsyncFail OBJECT-TYPE
			SYNTAX BitFail
			MAX-ACCESS read-only
			STATUS current
			DESCRIPTION
				"AES8 asynchronous fail"
		::= { deb2008c01v1Entry 181 }

		-- 1.3.6.1.4.1.10106.3.101291.1.1.183
		deb2008c01v1AsrcRefFail OBJECT-TYPE
			SYNTAX BitFail
			MAX-ACCESS read-only
			STATUS current
			DESCRIPTION
				"One or more ASRC reference inputs are missing"
		::= { deb2008c01v1Entry 183 }

		-- 1.3.6.1.4.1.10106.3.101291.1.1.185
		deb2008c01v1SerialNo OBJECT-TYPE
			SYNTAX SerialNo
			MAX-ACCESS read-only
			STATUS current
			DESCRIPTION
				"Serial number"
		::= { deb2008c01v1Entry 185 }

		-- 1.3.6.1.4.1.10106.3.607901
		def2008c01v1 OBJECT IDENTIFIER ::= { albalaProducts 607901 }

		-- 1.3.6.1.4.1.10106.3.607901.1
		def2008c01v1Table  OBJECT-TYPE
			SYNTAX SEQUENCE OF Def2008c01v1Entry
			MAX-ACCESS not-accessible
			STATUS current
			DESCRIPTION
				"Module  DEF2008C01V1 Table"
			::= { def2008c01v1 1 }

		-- 1.3.6.1.4.1.10106.3.607901.1.1
		def2008c01v1Entry  OBJECT-TYPE
			SYNTAX Def2008c01v1Entry
			MAX-ACCESS not-accessible
			STATUS current
			DESCRIPTION
				"Module DEF2008C01V1 Entry"
			INDEX { def2008c01v1Index }
			::= { def2008c01v1Table 1 }

			Def2008c01v1Entry ::=
			SEQUENCE {
				def2008c01v1Index
				ModuleIndex,
				def2008c01v1ActivePreset
				Preset16Active,
				def2008c01v1LoadPreset
				Preset16Load,
				def2008c01v1SavePreset
				Preset16Save,
				def2008c01v1AesIoMode
				IoAesModeRef,
				def2008c01v1AudioFailMode
				AudioFailMode,
				def2008c01v1Out1AsrcEn
				Bit0No1Yes,
				def2008c01v1Out2AsrcEn
				Bit0No1Yes,
				def2008c01v1Out3AsrcEn
				Bit0No1Yes,
				def2008c01v1Out4AsrcEn
				Bit0No1Yes,
				def2008c01v1In1Mode
				Bit0No1Yes,
				def2008c01v1In2Mode
				Bit0No1Yes,
				def2008c01v1In3Mode
				Bit0No1Yes,
				def2008c01v1In4Mode
				Bit0No1Yes,
				def2008c01v1In5Mode
				Bit0No1Yes,
				def2008c01v1In6Mode
				Bit0No1Yes,
				def2008c01v1In7Mode
				Bit0No1Yes,
				def2008c01v1In8Mode
				Bit0No1Yes,
				def2008c01v1AesIn1Pres
				BitFailN,
				def2008c01v1AesIn1PresTrapEnable
				AlarmEnable,
				def2008c01v1Aes1RefPres
				Bit0No1Yes,
				def2008c01v1Aes1RefPresTrapEnable
				AlarmEnable,
				def2008c01v1AesIn2Pres
				BitFailN,
				def2008c01v1AesIn2PresTrapEnable
				AlarmEnable,
				def2008c01v1Aes2RefPres
				Bit0No1Yes,
				def2008c01v1Aes2RefPresTrapEnable
				AlarmEnable,
				def2008c01v1AesIn3Pres
				BitFailN,
				def2008c01v1AesIn3PresTrapEnable
				AlarmEnable,
				def2008c01v1Aes3RefPres
				Bit0No1Yes,
				def2008c01v1Aes3RefPresTrapEnable
				AlarmEnable,
				def2008c01v1AesIn4Pres
				BitFailN,
				def2008c01v1AesIn4PresTrapEnable
				AlarmEnable,
				def2008c01v1Aes4RefPres
				Bit0No1Yes,
				def2008c01v1Aes4RefPresTrapEnable
				AlarmEnable,
				def2008c01v1AesIn5Pres
				BitFailN,
				def2008c01v1AesIn5PresTrapEnable
				AlarmEnable,
				def2008c01v1AesIn6Pres
				BitFailN,
				def2008c01v1AesIn6PresTrapEnable
				AlarmEnable,
				def2008c01v1AesIn7Pres
				BitFailN,
				def2008c01v1AesIn7PresTrapEnable
				AlarmEnable,
				def2008c01v1AesIn8Pres
				BitFailN,
				def2008c01v1AesIn8PresTrapEnable
				AlarmEnable,
				def2008c01v1AesIn1Locked
				BitFailN,
				def2008c01v1AesIn2Locked
				BitFailN,
				def2008c01v1AesIn3Locked
				BitFailN,
				def2008c01v1AesIn4Locked
				BitFailN,
				def2008c01v1AesIn5Locked
				BitFailN,
				def2008c01v1AesIn6Locked
				BitFailN,
				def2008c01v1AesIn7Locked
				BitFailN,
				def2008c01v1AesIn8Locked
				BitFailN,
				def2008c01v1BackplaneLocked
				BitFailN,
				def2008c01v1BackplaneLockedTrapEnable
				AlarmEnable,
				def2008c01v1L2rIn1Pres
				BitFailN,
				def2008c01v1L2rIn2Pres
				BitFailN,
				def2008c01v1L2rIn3Pres
				BitFailN,
				def2008c01v1L2rIn4Pres
				BitFailN,
				def2008c01v1L2rIn5Pres
				BitFailN,
				def2008c01v1L2rIn6Pres
				BitFailN,
				def2008c01v1L2rIn7Pres
				BitFailN,
				def2008c01v1L2rIn8Pres
				BitFailN,
				def2008c01v1L2rIn9Pres
				BitFailN,
				def2008c01v1L2rIn10Pres
				BitFailN,
				def2008c01v1L2rIn11Pres
				BitFailN,
				def2008c01v1L2rIn12Pres
				BitFailN,
				def2008c01v1L2rIn13Pres
				BitFailN,
				def2008c01v1L2rIn14Pres
				BitFailN,
				def2008c01v1L2rIn15Pres
				BitFailN,
				def2008c01v1L2rIn16Pres
				BitFailN,
				def2008c01v1R2lIn1Pres
				BitFailN,
				def2008c01v1R2lIn2Pres
				BitFailN,
				def2008c01v1R2lIn3Pres
				BitFailN,
				def2008c01v1R2lIn4Pres
				BitFailN,
				def2008c01v1R2lIn5Pres
				BitFailN,
				def2008c01v1R2lIn6Pres
				BitFailN,
				def2008c01v1R2lIn7Pres
				BitFailN,
				def2008c01v1R2lIn8Pres
				BitFailN,
				def2008c01v1R2lIn9Pres
				BitFailN,
				def2008c01v1R2lIn10Pres
				BitFailN,
				def2008c01v1R2lIn11Pres
				BitFailN,
				def2008c01v1R2lIn12Pres
				BitFailN,
				def2008c01v1R2lIn13Pres
				BitFailN,
				def2008c01v1R2lIn14Pres
				BitFailN,
				def2008c01v1R2lIn15Pres
				BitFailN,
				def2008c01v1R2lIn16Pres
				BitFailN,
				def2008c01v1SerialNo
				SerialNo
			 }

		-- 1.3.6.1.4.1.10106.3.101291.1.1.1
		def2008c01v1Index OBJECT-TYPE
			SYNTAX ModuleIndex
			MAX-ACCESS read-only
			STATUS current
			DESCRIPTION
				"Index of DEF2008C01V1 Table"
		::= { def2008c01v1Entry 1 }

		-- 1.3.6.1.4.1.10106.3.101291.1.1.3
		def2008c01v1ActivePreset OBJECT-TYPE
			SYNTAX Preset16Active
			MAX-ACCESS read-only
			STATUS current
			DESCRIPTION
				"Shows the active preset"
		::= { def2008c01v1Entry 3 }

		-- 1.3.6.1.4.1.10106.3.101291.1.1.5
		def2008c01v1LoadPreset OBJECT-TYPE
			SYNTAX Preset16Load
			MAX-ACCESS read-write
			STATUS current
			DESCRIPTION
				"Allows loading a preset"
		::= { def2008c01v1Entry 5 }

		-- 1.3.6.1.4.1.10106.3.101291.1.1.7
		def2008c01v1SavePreset OBJECT-TYPE
			SYNTAX Preset16Save
			MAX-ACCESS read-write
			STATUS current
			DESCRIPTION
				"Allows saving a preset"
		::= { def2008c01v1Entry 7 }

		-- 1.3.6.1.4.1.10106.3.101291.1.1.9
		def2008c01v1AesIoMode OBJECT-TYPE
			SYNTAX IoAesModeRef
			MAX-ACCESS read-write
			STATUS current
			DESCRIPTION
				"I/O AES mode"
		::= { def2008c01v1Entry 9 }

		-- 1.3.6.1.4.1.10106.3.101291.1.1.11
		def2008c01v1AudioFailMode OBJECT-TYPE
			SYNTAX AudioFailMode
			MAX-ACCESS read-write
			STATUS current
			DESCRIPTION
				"Allows selecting the output signal when the source signal fails"
		::= { def2008c01v1Entry 11 }

		-- 1.3.6.1.4.1.10106.3.101291.1.1.13
		def2008c01v1Out1AsrcEn OBJECT-TYPE
			SYNTAX Bit0No1Yes
			MAX-ACCESS read-write
			STATUS current
			DESCRIPTION
				"Enables ASRC in AES1 output"
		::= { def2008c01v1Entry 13 }

		-- 1.3.6.1.4.1.10106.3.101291.1.1.15
		def2008c01v1Out2AsrcEn OBJECT-TYPE
			SYNTAX Bit0No1Yes
			MAX-ACCESS read-write
			STATUS current
			DESCRIPTION
				"Enables ASRC in AES2 output"
		::= { def2008c01v1Entry 15 }

		-- 1.3.6.1.4.1.10106.3.101291.1.1.17
		def2008c01v1Out3AsrcEn OBJECT-TYPE
			SYNTAX Bit0No1Yes
			MAX-ACCESS read-write
			STATUS current
			DESCRIPTION
				"Enables ASRC in AES3 output"
		::= { def2008c01v1Entry 17 }

		-- 1.3.6.1.4.1.10106.3.101291.1.1.19
		def2008c01v1Out4AsrcEn OBJECT-TYPE
			SYNTAX Bit0No1Yes
			MAX-ACCESS read-write
			STATUS current
			DESCRIPTION
				"Enables ASRC in AES4 output"
		::= { def2008c01v1Entry 19 }

		-- 1.3.6.1.4.1.10106.3.101291.1.1.21
		def2008c01v1In1Mode OBJECT-TYPE
			SYNTAX Bit0No1Yes
			MAX-ACCESS read-write
			STATUS current
			DESCRIPTION
				"Enable ASRC in AES1 input"
		::= { def2008c01v1Entry 21 }

		-- 1.3.6.1.4.1.10106.3.101291.1.1.23
		def2008c01v1In2Mode OBJECT-TYPE
			SYNTAX Bit0No1Yes
			MAX-ACCESS read-write
			STATUS current
			DESCRIPTION
				"Enable ASRC in AES2 input"
		::= { def2008c01v1Entry 23 }

		-- 1.3.6.1.4.1.10106.3.101291.1.1.25
		def2008c01v1In3Mode OBJECT-TYPE
			SYNTAX Bit0No1Yes
			MAX-ACCESS read-write
			STATUS current
			DESCRIPTION
				"Enable ASRC in AES3 input"
		::= { def2008c01v1Entry 25 }

		-- 1.3.6.1.4.1.10106.3.101291.1.1.27
		def2008c01v1In4Mode OBJECT-TYPE
			SYNTAX Bit0No1Yes
			MAX-ACCESS read-write
			STATUS current
			DESCRIPTION
				"Enable ASRC in AES4 input"
		::= { def2008c01v1Entry 27 }

		-- 1.3.6.1.4.1.10106.3.101291.1.1.29
		def2008c01v1In5Mode OBJECT-TYPE
			SYNTAX Bit0No1Yes
			MAX-ACCESS read-write
			STATUS current
			DESCRIPTION
				"Enable ASRC in AES5 input"
		::= { def2008c01v1Entry 29 }

		-- 1.3.6.1.4.1.10106.3.101291.1.1.31
		def2008c01v1In6Mode OBJECT-TYPE
			SYNTAX Bit0No1Yes
			MAX-ACCESS read-write
			STATUS current
			DESCRIPTION
				"Enable ASRC in AES6 input"
		::= { def2008c01v1Entry 31 }

		-- 1.3.6.1.4.1.10106.3.101291.1.1.33
		def2008c01v1In7Mode OBJECT-TYPE
			SYNTAX Bit0No1Yes
			MAX-ACCESS read-write
			STATUS current
			DESCRIPTION
				"Enable ASRC in AES7 input"
		::= { def2008c01v1Entry 33 }

		-- 1.3.6.1.4.1.10106.3.101291.1.1.35
		def2008c01v1In8Mode OBJECT-TYPE
			SYNTAX Bit0No1Yes
			MAX-ACCESS read-write
			STATUS current
			DESCRIPTION
				"Enable ASRC in AES8 input"
		::= { def2008c01v1Entry 35 }

		-- 1.3.6.1.4.1.10106.3.101291.1.1.37
		def2008c01v1AesIn1Pres OBJECT-TYPE
			SYNTAX BitFailN
			MAX-ACCESS read-only
			STATUS current
			DESCRIPTION
				"AES1 IN presence (valid signal)"
		::= { def2008c01v1Entry 37 }

		-- 1.3.6.1.4.1.10106.3.101291.1.1.38
		def2008c01v1AesIn1PresTrapEnable OBJECT-TYPE
			SYNTAX AlarmEnable
			MAX-ACCESS read-write
			STATUS current
			DESCRIPTION
				"AES1 IN presence (valid signal) Trap Enable"
		::= { def2008c01v1Entry 38 }

		-- 1.3.6.1.4.1.10106.3.101291.1.1.39
		def2008c01v1Aes1RefPres OBJECT-TYPE
			SYNTAX Bit0No1Yes
			MAX-ACCESS read-only
			STATUS current
			DESCRIPTION
				"AES1 reference presence"
		::= { def2008c01v1Entry 39 }

		-- 1.3.6.1.4.1.10106.3.101291.1.1.40
		def2008c01v1Aes1RefPresTrapEnable OBJECT-TYPE
			SYNTAX AlarmEnable
			MAX-ACCESS read-write
			STATUS current
			DESCRIPTION
				"AES1 reference presence Trap Enable"
		::= { def2008c01v1Entry 40 }

		-- 1.3.6.1.4.1.10106.3.101291.1.1.41
		def2008c01v1AesIn2Pres OBJECT-TYPE
			SYNTAX BitFailN
			MAX-ACCESS read-only
			STATUS current
			DESCRIPTION
				"AES2 IN presence (valid signal)"
		::= { def2008c01v1Entry 41 }

		-- 1.3.6.1.4.1.10106.3.101291.1.1.42
		def2008c01v1AesIn2PresTrapEnable OBJECT-TYPE
			SYNTAX AlarmEnable
			MAX-ACCESS read-write
			STATUS current
			DESCRIPTION
				"AES2 IN presence (valid signal) Trap Enable"
		::= { def2008c01v1Entry 42 }

		-- 1.3.6.1.4.1.10106.3.101291.1.1.43
		def2008c01v1Aes2RefPres OBJECT-TYPE
			SYNTAX Bit0No1Yes
			MAX-ACCESS read-only
			STATUS current
			DESCRIPTION
				"AES2 reference presence"
		::= { def2008c01v1Entry 43 }

		-- 1.3.6.1.4.1.10106.3.101291.1.1.44
		def2008c01v1Aes2RefPresTrapEnable OBJECT-TYPE
			SYNTAX AlarmEnable
			MAX-ACCESS read-write
			STATUS current
			DESCRIPTION
				"AES2 reference presence Trap Enable"
		::= { def2008c01v1Entry 44 }

		-- 1.3.6.1.4.1.10106.3.101291.1.1.45
		def2008c01v1AesIn3Pres OBJECT-TYPE
			SYNTAX BitFailN
			MAX-ACCESS read-only
			STATUS current
			DESCRIPTION
				"AES3 IN presence (valid signal)"
		::= { def2008c01v1Entry 45 }

		-- 1.3.6.1.4.1.10106.3.101291.1.1.46
		def2008c01v1AesIn3PresTrapEnable OBJECT-TYPE
			SYNTAX AlarmEnable
			MAX-ACCESS read-write
			STATUS current
			DESCRIPTION
				"AES3 IN presence (valid signal) Trap Enable"
		::= { def2008c01v1Entry 46 }

		-- 1.3.6.1.4.1.10106.3.101291.1.1.47
		def2008c01v1Aes3RefPres OBJECT-TYPE
			SYNTAX Bit0No1Yes
			MAX-ACCESS read-only
			STATUS current
			DESCRIPTION
				"AES3 reference presence"
		::= { def2008c01v1Entry 47 }

		-- 1.3.6.1.4.1.10106.3.101291.1.1.48
		def2008c01v1Aes3RefPresTrapEnable OBJECT-TYPE
			SYNTAX AlarmEnable
			MAX-ACCESS read-write
			STATUS current
			DESCRIPTION
				"AES3 reference presence Trap Enable"
		::= { def2008c01v1Entry 48 }

		-- 1.3.6.1.4.1.10106.3.101291.1.1.49
		def2008c01v1AesIn4Pres OBJECT-TYPE
			SYNTAX BitFailN
			MAX-ACCESS read-only
			STATUS current
			DESCRIPTION
				"AES4 IN presence (valid signal)"
		::= { def2008c01v1Entry 49 }

		-- 1.3.6.1.4.1.10106.3.101291.1.1.50
		def2008c01v1AesIn4PresTrapEnable OBJECT-TYPE
			SYNTAX AlarmEnable
			MAX-ACCESS read-write
			STATUS current
			DESCRIPTION
				"AES4 IN presence (valid signal) Trap Enable"
		::= { def2008c01v1Entry 50 }

		-- 1.3.6.1.4.1.10106.3.101291.1.1.51
		def2008c01v1Aes4RefPres OBJECT-TYPE
			SYNTAX Bit0No1Yes
			MAX-ACCESS read-only
			STATUS current
			DESCRIPTION
				"AES4 reference presence"
		::= { def2008c01v1Entry 51 }

		-- 1.3.6.1.4.1.10106.3.101291.1.1.52
		def2008c01v1Aes4RefPresTrapEnable OBJECT-TYPE
			SYNTAX AlarmEnable
			MAX-ACCESS read-write
			STATUS current
			DESCRIPTION
				"AES4 reference presence Trap Enable"
		::= { def2008c01v1Entry 52 }

		-- 1.3.6.1.4.1.10106.3.101291.1.1.53
		def2008c01v1AesIn5Pres OBJECT-TYPE
			SYNTAX BitFailN
			MAX-ACCESS read-only
			STATUS current
			DESCRIPTION
				"AES5 IN presence (valid signal)"
		::= { def2008c01v1Entry 53 }

		-- 1.3.6.1.4.1.10106.3.101291.1.1.54
		def2008c01v1AesIn5PresTrapEnable OBJECT-TYPE
			SYNTAX AlarmEnable
			MAX-ACCESS read-write
			STATUS current
			DESCRIPTION
				"AES5 IN presence (valid signal) Trap Enable"
		::= { def2008c01v1Entry 54 }

		-- 1.3.6.1.4.1.10106.3.101291.1.1.55
		def2008c01v1AesIn6Pres OBJECT-TYPE
			SYNTAX BitFailN
			MAX-ACCESS read-only
			STATUS current
			DESCRIPTION
				"AES6 IN presence (valid signal)"
		::= { def2008c01v1Entry 55 }

		-- 1.3.6.1.4.1.10106.3.101291.1.1.56
		def2008c01v1AesIn6PresTrapEnable OBJECT-TYPE
			SYNTAX AlarmEnable
			MAX-ACCESS read-write
			STATUS current
			DESCRIPTION
				"AES6 IN presence (valid signal) Trap Enable"
		::= { def2008c01v1Entry 56 }

		-- 1.3.6.1.4.1.10106.3.101291.1.1.57
		def2008c01v1AesIn7Pres OBJECT-TYPE
			SYNTAX BitFailN
			MAX-ACCESS read-only
			STATUS current
			DESCRIPTION
				"AES7 IN presence (valid signal)"
		::= { def2008c01v1Entry 57 }

		-- 1.3.6.1.4.1.10106.3.101291.1.1.58
		def2008c01v1AesIn7PresTrapEnable OBJECT-TYPE
			SYNTAX AlarmEnable
			MAX-ACCESS read-write
			STATUS current
			DESCRIPTION
				"AES7 IN presence (valid signal) Trap Enable"
		::= { def2008c01v1Entry 58 }

		-- 1.3.6.1.4.1.10106.3.101291.1.1.59
		def2008c01v1AesIn8Pres OBJECT-TYPE
			SYNTAX BitFailN
			MAX-ACCESS read-only
			STATUS current
			DESCRIPTION
				"AES8 IN presence (valid signal)"
		::= { def2008c01v1Entry 59 }

		-- 1.3.6.1.4.1.10106.3.101291.1.1.60
		def2008c01v1AesIn8PresTrapEnable OBJECT-TYPE
			SYNTAX AlarmEnable
			MAX-ACCESS read-write
			STATUS current
			DESCRIPTION
				"AES8 IN presence (valid signal) Trap Enable"
		::= { def2008c01v1Entry 60 }

		-- 1.3.6.1.4.1.10106.3.101291.1.1.61
		def2008c01v1AesIn1Locked OBJECT-TYPE
			SYNTAX BitFailN
			MAX-ACCESS read-only
			STATUS current
			DESCRIPTION
				"AES1 IN locked (synchronized with internal clock)"
		::= { def2008c01v1Entry 61 }

		-- 1.3.6.1.4.1.10106.3.101291.1.1.63
		def2008c01v1AesIn2Locked OBJECT-TYPE
			SYNTAX BitFailN
			MAX-ACCESS read-only
			STATUS current
			DESCRIPTION
				"AES2 IN locked (synchronized with internal clock)"
		::= { def2008c01v1Entry 63 }

		-- 1.3.6.1.4.1.10106.3.101291.1.1.65
		def2008c01v1AesIn3Locked OBJECT-TYPE
			SYNTAX BitFailN
			MAX-ACCESS read-only
			STATUS current
			DESCRIPTION
				"AES3 IN locked (synchronized with internal clock)"
		::= { def2008c01v1Entry 65 }

		-- 1.3.6.1.4.1.10106.3.101291.1.1.67
		def2008c01v1AesIn4Locked OBJECT-TYPE
			SYNTAX BitFailN
			MAX-ACCESS read-only
			STATUS current
			DESCRIPTION
				"AES4 IN locked (synchronized with internal clock)"
		::= { def2008c01v1Entry 67 }

		-- 1.3.6.1.4.1.10106.3.101291.1.1.69
		def2008c01v1AesIn5Locked OBJECT-TYPE
			SYNTAX BitFailN
			MAX-ACCESS read-only
			STATUS current
			DESCRIPTION
				"AES5 IN locked (synchronized with internal clock)"
		::= { def2008c01v1Entry 69 }

		-- 1.3.6.1.4.1.10106.3.101291.1.1.71
		def2008c01v1AesIn6Locked OBJECT-TYPE
			SYNTAX BitFailN
			MAX-ACCESS read-only
			STATUS current
			DESCRIPTION
				"AES6 IN locked (synchronized with internal clock)"
		::= { def2008c01v1Entry 71 }

		-- 1.3.6.1.4.1.10106.3.101291.1.1.73
		def2008c01v1AesIn7Locked OBJECT-TYPE
			SYNTAX BitFailN
			MAX-ACCESS read-only
			STATUS current
			DESCRIPTION
				"AES7 IN locked (synchronized with internal clock)"
		::= { def2008c01v1Entry 73 }

		-- 1.3.6.1.4.1.10106.3.101291.1.1.75
		def2008c01v1AesIn8Locked OBJECT-TYPE
			SYNTAX BitFailN
			MAX-ACCESS read-only
			STATUS current
			DESCRIPTION
				"AES8 IN locked (synchronized with internal clock)"
		::= { def2008c01v1Entry 75 }

		-- 1.3.6.1.4.1.10106.3.101291.1.1.77
		def2008c01v1BackplaneLocked OBJECT-TYPE
			SYNTAX BitFailN
			MAX-ACCESS read-only
			STATUS current
			DESCRIPTION
				"Locked to internal bus audio (MCLK and WCLK valid and locked)"
		::= { def2008c01v1Entry 77 }

		-- 1.3.6.1.4.1.10106.3.101291.1.1.78
		def2008c01v1BackplaneLockedTrapEnable OBJECT-TYPE
			SYNTAX AlarmEnable
			MAX-ACCESS read-write
			STATUS current
			DESCRIPTION
				"Locked to internal bus audio (MCLK and WCLK valid and locked) Trap Enable"
		::= { def2008c01v1Entry 78 }

		-- 1.3.6.1.4.1.10106.3.101291.1.1.79
		def2008c01v1L2rIn1Pres OBJECT-TYPE
			SYNTAX BitFailN
			MAX-ACCESS read-only
			STATUS current
			DESCRIPTION
				"There is a valid audio signal in channel 1 of  L2R IN"
		::= { def2008c01v1Entry 79 }

		-- 1.3.6.1.4.1.10106.3.101291.1.1.81
		def2008c01v1L2rIn2Pres OBJECT-TYPE
			SYNTAX BitFailN
			MAX-ACCESS read-only
			STATUS current
			DESCRIPTION
				"There is a valid audio signal in channel 2 of  L2R IN"
		::= { def2008c01v1Entry 81 }

		-- 1.3.6.1.4.1.10106.3.101291.1.1.83
		def2008c01v1L2rIn3Pres OBJECT-TYPE
			SYNTAX BitFailN
			MAX-ACCESS read-only
			STATUS current
			DESCRIPTION
				"There is a valid audio signal in channel 3 of  L2R IN"
		::= { def2008c01v1Entry 83 }

		-- 1.3.6.1.4.1.10106.3.101291.1.1.85
		def2008c01v1L2rIn4Pres OBJECT-TYPE
			SYNTAX BitFailN
			MAX-ACCESS read-only
			STATUS current
			DESCRIPTION
				"There is a valid audio signal in channel 4 of  L2R IN"
		::= { def2008c01v1Entry 85 }

		-- 1.3.6.1.4.1.10106.3.101291.1.1.87
		def2008c01v1L2rIn5Pres OBJECT-TYPE
			SYNTAX BitFailN
			MAX-ACCESS read-only
			STATUS current
			DESCRIPTION
				"There is a valid audio signal in channel 5 of  L2R IN"
		::= { def2008c01v1Entry 87 }

		-- 1.3.6.1.4.1.10106.3.101291.1.1.89
		def2008c01v1L2rIn6Pres OBJECT-TYPE
			SYNTAX BitFailN
			MAX-ACCESS read-only
			STATUS current
			DESCRIPTION
				"There is a valid audio signal in channel 6 of  L2R IN"
		::= { def2008c01v1Entry 89 }

		-- 1.3.6.1.4.1.10106.3.101291.1.1.91
		def2008c01v1L2rIn7Pres OBJECT-TYPE
			SYNTAX BitFailN
			MAX-ACCESS read-only
			STATUS current
			DESCRIPTION
				"There is a valid audio signal in channel 7 of  L2R IN"
		::= { def2008c01v1Entry 91 }

		-- 1.3.6.1.4.1.10106.3.101291.1.1.93
		def2008c01v1L2rIn8Pres OBJECT-TYPE
			SYNTAX BitFailN
			MAX-ACCESS read-only
			STATUS current
			DESCRIPTION
				"There is a valid audio signal in channel 8 of  L2R IN"
		::= { def2008c01v1Entry 93 }

		-- 1.3.6.1.4.1.10106.3.101291.1.1.95
		def2008c01v1L2rIn9Pres OBJECT-TYPE
			SYNTAX BitFailN
			MAX-ACCESS read-only
			STATUS current
			DESCRIPTION
				"There is a valid audio signal in channel 9 of  L2R IN"
		::= { def2008c01v1Entry 95 }

		-- 1.3.6.1.4.1.10106.3.101291.1.1.97
		def2008c01v1L2rIn10Pres OBJECT-TYPE
			SYNTAX BitFailN
			MAX-ACCESS read-only
			STATUS current
			DESCRIPTION
				"There is a valid audio signal in channel 10 of  L2R IN"
		::= { def2008c01v1Entry 97 }

		-- 1.3.6.1.4.1.10106.3.101291.1.1.99
		def2008c01v1L2rIn11Pres OBJECT-TYPE
			SYNTAX BitFailN
			MAX-ACCESS read-only
			STATUS current
			DESCRIPTION
				"There is a valid audio signal in channel 11 of  L2R IN"
		::= { def2008c01v1Entry 99 }

		-- 1.3.6.1.4.1.10106.3.101291.1.1.101
		def2008c01v1L2rIn12Pres OBJECT-TYPE
			SYNTAX BitFailN
			MAX-ACCESS read-only
			STATUS current
			DESCRIPTION
				"There is a valid audio signal in channel 12 of  L2R IN"
		::= { def2008c01v1Entry 101 }

		-- 1.3.6.1.4.1.10106.3.101291.1.1.103
		def2008c01v1L2rIn13Pres OBJECT-TYPE
			SYNTAX BitFailN
			MAX-ACCESS read-only
			STATUS current
			DESCRIPTION
				"There is a valid audio signal in channel 13 of  L2R IN"
		::= { def2008c01v1Entry 103 }

		-- 1.3.6.1.4.1.10106.3.101291.1.1.105
		def2008c01v1L2rIn14Pres OBJECT-TYPE
			SYNTAX BitFailN
			MAX-ACCESS read-only
			STATUS current
			DESCRIPTION
				"There is a valid audio signal in channel 14 of  L2R IN"
		::= { def2008c01v1Entry 105 }

		-- 1.3.6.1.4.1.10106.3.101291.1.1.107
		def2008c01v1L2rIn15Pres OBJECT-TYPE
			SYNTAX BitFailN
			MAX-ACCESS read-only
			STATUS current
			DESCRIPTION
				"There is a valid audio signal in channel 15 of  L2R IN"
		::= { def2008c01v1Entry 107 }

		-- 1.3.6.1.4.1.10106.3.101291.1.1.109
		def2008c01v1L2rIn16Pres OBJECT-TYPE
			SYNTAX BitFailN
			MAX-ACCESS read-only
			STATUS current
			DESCRIPTION
				"There is a valid audio signal in channel 16 of  L2R IN"
		::= { def2008c01v1Entry 109 }

		-- 1.3.6.1.4.1.10106.3.101291.1.1.111
		def2008c01v1R2lIn1Pres OBJECT-TYPE
			SYNTAX BitFailN
			MAX-ACCESS read-only
			STATUS current
			DESCRIPTION
				"There is a valid audio signal in channel 1 of  R2L IN"
		::= { def2008c01v1Entry 111 }

		-- 1.3.6.1.4.1.10106.3.101291.1.1.113
		def2008c01v1R2lIn2Pres OBJECT-TYPE
			SYNTAX BitFailN
			MAX-ACCESS read-only
			STATUS current
			DESCRIPTION
				"There is a valid audio signal in channel 2 of  R2L IN"
		::= { def2008c01v1Entry 113 }

		-- 1.3.6.1.4.1.10106.3.101291.1.1.115
		def2008c01v1R2lIn3Pres OBJECT-TYPE
			SYNTAX BitFailN
			MAX-ACCESS read-only
			STATUS current
			DESCRIPTION
				"There is a valid audio signal in channel 3 of  R2L IN"
		::= { def2008c01v1Entry 115 }

		-- 1.3.6.1.4.1.10106.3.101291.1.1.117
		def2008c01v1R2lIn4Pres OBJECT-TYPE
			SYNTAX BitFailN
			MAX-ACCESS read-only
			STATUS current
			DESCRIPTION
				"There is a valid audio signal in channel 4 of  R2L IN"
		::= { def2008c01v1Entry 117 }

		-- 1.3.6.1.4.1.10106.3.101291.1.1.119
		def2008c01v1R2lIn5Pres OBJECT-TYPE
			SYNTAX BitFailN
			MAX-ACCESS read-only
			STATUS current
			DESCRIPTION
				"There is a valid audio signal in channel 5 of  R2L IN"
		::= { def2008c01v1Entry 119 }

		-- 1.3.6.1.4.1.10106.3.101291.1.1.121
		def2008c01v1R2lIn6Pres OBJECT-TYPE
			SYNTAX BitFailN
			MAX-ACCESS read-only
			STATUS current
			DESCRIPTION
				"There is a valid audio signal in channel 6 of  R2L IN"
		::= { def2008c01v1Entry 121 }

		-- 1.3.6.1.4.1.10106.3.101291.1.1.123
		def2008c01v1R2lIn7Pres OBJECT-TYPE
			SYNTAX BitFailN
			MAX-ACCESS read-only
			STATUS current
			DESCRIPTION
				"There is a valid audio signal in channel 7 of  R2L IN"
		::= { def2008c01v1Entry 123 }

		-- 1.3.6.1.4.1.10106.3.101291.1.1.125
		def2008c01v1R2lIn8Pres OBJECT-TYPE
			SYNTAX BitFailN
			MAX-ACCESS read-only
			STATUS current
			DESCRIPTION
				"There is a valid audio signal in channel 8 of  R2L IN"
		::= { def2008c01v1Entry 125 }

		-- 1.3.6.1.4.1.10106.3.101291.1.1.127
		def2008c01v1R2lIn9Pres OBJECT-TYPE
			SYNTAX BitFailN
			MAX-ACCESS read-only
			STATUS current
			DESCRIPTION
				"There is a valid audio signal in channel 9 of  R2L IN"
		::= { def2008c01v1Entry 127 }

		-- 1.3.6.1.4.1.10106.3.101291.1.1.129
		def2008c01v1R2lIn10Pres OBJECT-TYPE
			SYNTAX BitFailN
			MAX-ACCESS read-only
			STATUS current
			DESCRIPTION
				"There is a valid audio signal in channel 10 of  R2L IN"
		::= { def2008c01v1Entry 129 }

		-- 1.3.6.1.4.1.10106.3.101291.1.1.131
		def2008c01v1R2lIn11Pres OBJECT-TYPE
			SYNTAX BitFailN
			MAX-ACCESS read-only
			STATUS current
			DESCRIPTION
				"There is a valid audio signal in channel 11 of  R2L IN"
		::= { def2008c01v1Entry 131 }

		-- 1.3.6.1.4.1.10106.3.101291.1.1.133
		def2008c01v1R2lIn12Pres OBJECT-TYPE
			SYNTAX BitFailN
			MAX-ACCESS read-only
			STATUS current
			DESCRIPTION
				"There is a valid audio signal in channel 12 of  R2L IN"
		::= { def2008c01v1Entry 133 }

		-- 1.3.6.1.4.1.10106.3.101291.1.1.135
		def2008c01v1R2lIn13Pres OBJECT-TYPE
			SYNTAX BitFailN
			MAX-ACCESS read-only
			STATUS current
			DESCRIPTION
				"There is a valid audio signal in channel 13 of  R2L IN"
		::= { def2008c01v1Entry 135 }

		-- 1.3.6.1.4.1.10106.3.101291.1.1.137
		def2008c01v1R2lIn14Pres OBJECT-TYPE
			SYNTAX BitFailN
			MAX-ACCESS read-only
			STATUS current
			DESCRIPTION
				"There is a valid audio signal in channel 14 of  R2L IN"
		::= { def2008c01v1Entry 137 }

		-- 1.3.6.1.4.1.10106.3.101291.1.1.139
		def2008c01v1R2lIn15Pres OBJECT-TYPE
			SYNTAX BitFailN
			MAX-ACCESS read-only
			STATUS current
			DESCRIPTION
				"There is a valid audio signal in channel 15 of  R2L IN"
		::= { def2008c01v1Entry 139 }

		-- 1.3.6.1.4.1.10106.3.101291.1.1.141
		def2008c01v1R2lIn16Pres OBJECT-TYPE
			SYNTAX BitFailN
			MAX-ACCESS read-only
			STATUS current
			DESCRIPTION
				"There is a valid audio signal in channel 16 of  R2L IN"
		::= { def2008c01v1Entry 141 }

		-- 1.3.6.1.4.1.10106.3.101291.1.1.143
		def2008c01v1SerialNo OBJECT-TYPE
			SYNTAX SerialNo
			MAX-ACCESS read-only
			STATUS current
			DESCRIPTION
				"Serial number"
		::= { def2008c01v1Entry 143 }

		-- 1.3.6.1.4.1.10106.3.609201
		dad2000c01v1 OBJECT IDENTIFIER ::= { albalaProducts 609201 }

		-- 1.3.6.1.4.1.10106.3.609201.1
		dad2000c01v1Table  OBJECT-TYPE
			SYNTAX SEQUENCE OF Dad2000c01v1Entry
			MAX-ACCESS not-accessible
			STATUS current
			DESCRIPTION
				"Module  DAD2000C01V1 Table"
			::= { dad2000c01v1 1 }

		-- 1.3.6.1.4.1.10106.3.609201.1.1
		dad2000c01v1Entry  OBJECT-TYPE
			SYNTAX Dad2000c01v1Entry
			MAX-ACCESS not-accessible
			STATUS current
			DESCRIPTION
				"Module DAD2000C01V1 Entry"
			INDEX { dad2000c01v1Index }
			::= { dad2000c01v1Table 1 }

			Dad2000c01v1Entry ::=
			SEQUENCE {
				dad2000c01v1Index
				ModuleIndex,
				dad2000c01v1SigFail
				BitFail,
				dad2000c01v1SigFailTrapEnable
				AlarmEnable,
				dad2000c01v1SigLow
				BitFail,
				dad2000c01v1SigLowTrapEnable
				AlarmEnable,
				dad2000c01v1SignalLevel
				Dad2Level
			 }

		-- 1.3.6.1.4.1.10106.3.101291.1.1.1
		dad2000c01v1Index OBJECT-TYPE
			SYNTAX ModuleIndex
			MAX-ACCESS read-only
			STATUS current
			DESCRIPTION
				"Index of DAD2000C01V1 Table"
		::= { dad2000c01v1Entry 1 }

		-- 1.3.6.1.4.1.10106.3.101291.1.1.3
		dad2000c01v1SigFail OBJECT-TYPE
			SYNTAX BitFail
			MAX-ACCESS read-only
			STATUS current
			DESCRIPTION
				"Indicates that a signal fail has been detected"
		::= { dad2000c01v1Entry 3 }

		-- 1.3.6.1.4.1.10106.3.101291.1.1.4
		dad2000c01v1SigFailTrapEnable OBJECT-TYPE
			SYNTAX AlarmEnable
			MAX-ACCESS read-write
			STATUS current
			DESCRIPTION
				"Indicates that a signal fail has been detected Trap Enable"
		::= { dad2000c01v1Entry 4 }

		-- 1.3.6.1.4.1.10106.3.101291.1.1.5
		dad2000c01v1SigLow OBJECT-TYPE
			SYNTAX BitFail
			MAX-ACCESS read-only
			STATUS current
			DESCRIPTION
				"Indicates that a signal low has been detected"
		::= { dad2000c01v1Entry 5 }

		-- 1.3.6.1.4.1.10106.3.101291.1.1.6
		dad2000c01v1SigLowTrapEnable OBJECT-TYPE
			SYNTAX AlarmEnable
			MAX-ACCESS read-write
			STATUS current
			DESCRIPTION
				"Indicates that a signal low has been detected Trap Enable"
		::= { dad2000c01v1Entry 6 }

		-- 1.3.6.1.4.1.10106.3.101291.1.1.7
		dad2000c01v1SignalLevel OBJECT-TYPE
			SYNTAX Dad2Level
			MAX-ACCESS read-only
			STATUS current
			DESCRIPTION
				"Signal amplitude"
		::= { dad2000c01v1Entry 7 }

		-- 1.3.6.1.4.1.10106.3.612801
		vtr2000c01v1 OBJECT IDENTIFIER ::= { albalaProducts 612801 }

		-- 1.3.6.1.4.1.10106.3.612801.1
		vtr2000c01v1Table  OBJECT-TYPE
			SYNTAX SEQUENCE OF Vtr2000c01v1Entry
			MAX-ACCESS not-accessible
			STATUS current
			DESCRIPTION
				"Module  VTR2000C01V1 Table"
			::= { vtr2000c01v1 1 }

		-- 1.3.6.1.4.1.10106.3.612801.1.1
		vtr2000c01v1Entry  OBJECT-TYPE
			SYNTAX Vtr2000c01v1Entry
			MAX-ACCESS not-accessible
			STATUS current
			DESCRIPTION
				"Module VTR2000C01V1 Entry"
			INDEX { vtr2000c01v1Index }
			::= { vtr2000c01v1Table 1 }

			Vtr2000c01v1Entry ::=
			SEQUENCE {
				vtr2000c01v1Index
				ModuleIndex,
				vtr2000c01v1ActivePreset
				Preset16Active,
				vtr2000c01v1LoadPreset
				Preset16Load,
				vtr2000c01v1SavePreset
				Preset16Save,
				vtr2000c01v1TcSrc1
				TcSource,
				vtr2000c01v1TcSrc2
				TcSource,
				vtr2000c01v1EnLtcIn
				Bit0No1Yes,
				vtr2000c01v1TcToTs
				Bit0No1Yes,
				vtr2000c01v1LtcEmbSrc1
				AudioMxInput6,
				vtr2000c01v1LtcEmbSrc2
				AudioMxInput6,
				vtr2000c01v1MeasType
				VtrMeasType,
				vtr2000c01v1MeasLdOff
				Bit0No1Yes,
				vtr2000c01v1MeasOffSign
				Bit0Pos1Neg,
				vtr2000c01v1IpAdd0
				Uint8,
				vtr2000c01v1IpAdd1
				Uint8,
				vtr2000c01v1IpAdd2
				Uint8,
				vtr2000c01v1IpAdd3
				Uint8,
				vtr2000c01v1IpMask0
				Uint8,
				vtr2000c01v1IpMask1
				Uint8,
				vtr2000c01v1IpMask2
				Uint8,
				vtr2000c01v1IpMask3
				Uint8,
				vtr2000c01v1IpGway0
				Uint8,
				vtr2000c01v1IpGway1
				Uint8,
				vtr2000c01v1IpGway2
				Uint8,
				vtr2000c01v1IpGway3
				Uint8,
				vtr2000c01v1NtpIpAddress0
				Uint8,
				vtr2000c01v1NtpIpAddress1
				Uint8,
				vtr2000c01v1NtpIpAddress2
				Uint8,
				vtr2000c01v1NtpIpAddress3
				Uint8,
				vtr2000c01v1Measure
				TimeX1MsInt32,
				vtr2000c01v1Format1
				SdiHd3gFmt3,
				vtr2000c01v1SdiInvalid1
				BitFail,
				vtr2000c01v1NoSignal1
				BitFail,
				vtr2000c01v1CrcErr1
				BitFail,
				vtr2000c01v1TcSrcFail1
				BitFail,
				vtr2000c01v1AtcVitcPres1
				BitFailN,
				vtr2000c01v1AtcLtcPres1
				BitFailN,
				vtr2000c01v1DvitcPres1
				BitFailN,
				vtr2000c01v1LtcEmbPres1
				BitFailN,
				vtr2000c01v1AudGrpPres11
				BitFailN,
				vtr2000c01v1AudGrpPres12
				BitFailN,
				vtr2000c01v1AudGrpPres13
				BitFailN,
				vtr2000c01v1AudGrpPres14
				BitFailN,
				vtr2000c01v1Format2
				SdiHd3gFmt3,
				vtr2000c01v1SdiInvalid2
				BitFail,
				vtr2000c01v1NoSignal2
				BitFail,
				vtr2000c01v1CrcErr2
				BitFail,
				vtr2000c01v1TcSrcFail2
				BitFail,
				vtr2000c01v1AtcVitcPres2
				BitFailN,
				vtr2000c01v1AtcLtcPres2
				BitFailN,
				vtr2000c01v1DvitcPres2
				BitFailN,
				vtr2000c01v1LtcEmbPres2
				BitFailN,
				vtr2000c01v1AudGrpPres21
				BitFailN,
				vtr2000c01v1AudGrpPres22
				BitFailN,
				vtr2000c01v1AudGrpPres23
				BitFailN,
				vtr2000c01v1AudGrpPres24
				BitFailN,
				vtr2000c01v1LtcInFail
				BitFail,
				vtr2000c01v1BusRefFail
				BitFail,
				vtr2000c01v1LockSrc
				VtrLockSrc,
				vtr2000c01v1MeasRdy
				BitFailN,
				vtr2000c01v1EthLink
				Ipa2EtherStat,
				vtr2000c01v1EthSystem
				Ipa2EtherSys,
				vtr2000c01v1SerialNo
				SerialNo
			 }

		-- 1.3.6.1.4.1.10106.3.101291.1.1.1
		vtr2000c01v1Index OBJECT-TYPE
			SYNTAX ModuleIndex
			MAX-ACCESS read-only
			STATUS current
			DESCRIPTION
				"Index of VTR2000C01V1 Table"
		::= { vtr2000c01v1Entry 1 }

		-- 1.3.6.1.4.1.10106.3.101291.1.1.3
		vtr2000c01v1ActivePreset OBJECT-TYPE
			SYNTAX Preset16Active
			MAX-ACCESS read-only
			STATUS current
			DESCRIPTION
				"Shows the active preset"
		::= { vtr2000c01v1Entry 3 }

		-- 1.3.6.1.4.1.10106.3.101291.1.1.5
		vtr2000c01v1LoadPreset OBJECT-TYPE
			SYNTAX Preset16Load
			MAX-ACCESS read-write
			STATUS current
			DESCRIPTION
				"Allows loading a preset"
		::= { vtr2000c01v1Entry 5 }

		-- 1.3.6.1.4.1.10106.3.101291.1.1.7
		vtr2000c01v1SavePreset OBJECT-TYPE
			SYNTAX Preset16Save
			MAX-ACCESS read-write
			STATUS current
			DESCRIPTION
				"Allows saving a preset"
		::= { vtr2000c01v1Entry 7 }

		-- 1.3.6.1.4.1.10106.3.101291.1.1.9
		vtr2000c01v1TcSrc1 OBJECT-TYPE
			SYNTAX TcSource
			MAX-ACCESS read-write
			STATUS current
			DESCRIPTION
				"Selected timecode source for this input"
		::= { vtr2000c01v1Entry 9 }

		-- 1.3.6.1.4.1.10106.3.101291.1.1.11
		vtr2000c01v1TcSrc2 OBJECT-TYPE
			SYNTAX TcSource
			MAX-ACCESS read-write
			STATUS current
			DESCRIPTION
				"Selected timecode source for this input"
		::= { vtr2000c01v1Entry 11 }

		-- 1.3.6.1.4.1.10106.3.101291.1.1.13
		vtr2000c01v1EnLtcIn OBJECT-TYPE
			SYNTAX Bit0No1Yes
			MAX-ACCESS read-write
			STATUS current
			DESCRIPTION
				"Enables analog LTC input to be used instead of SDI IN2"
		::= { vtr2000c01v1Entry 13 }

		-- 1.3.6.1.4.1.10106.3.101291.1.1.15
		vtr2000c01v1TcToTs OBJECT-TYPE
			SYNTAX Bit0No1Yes
			MAX-ACCESS read-write
			STATUS current
			DESCRIPTION
				"When 13.5 MHz bus reference is not available"
		::= { vtr2000c01v1Entry 15 }

		-- 1.3.6.1.4.1.10106.3.101291.1.1.17
		vtr2000c01v1LtcEmbSrc1 OBJECT-TYPE
			SYNTAX AudioMxInput6
			MAX-ACCESS read-write
			STATUS current
			DESCRIPTION
				"Embedded audio channel used as LTC source"
		::= { vtr2000c01v1Entry 17 }

		-- 1.3.6.1.4.1.10106.3.101291.1.1.19
		vtr2000c01v1LtcEmbSrc2 OBJECT-TYPE
			SYNTAX AudioMxInput6
			MAX-ACCESS read-write
			STATUS current
			DESCRIPTION
				"Embedded audio channel used as LTC source"
		::= { vtr2000c01v1Entry 19 }

		-- 1.3.6.1.4.1.10106.3.101291.1.1.21
		vtr2000c01v1MeasType OBJECT-TYPE
			SYNTAX VtrMeasType
			MAX-ACCESS read-write
			STATUS current
			DESCRIPTION
				"Selects the type of measurement to be shown"
		::= { vtr2000c01v1Entry 21 }

		-- 1.3.6.1.4.1.10106.3.101291.1.1.23
		vtr2000c01v1MeasLdOff OBJECT-TYPE
			SYNTAX Bit0No1Yes
			MAX-ACCESS read-write
			STATUS current
			DESCRIPTION
				"Sets the current measurement as the new offset"
		::= { vtr2000c01v1Entry 23 }

		-- 1.3.6.1.4.1.10106.3.101291.1.1.25
		vtr2000c01v1MeasOffSign OBJECT-TYPE
			SYNTAX Bit0Pos1Neg
			MAX-ACCESS read-write
			STATUS current
			DESCRIPTION
				"Sets the measurement offset sign"
		::= { vtr2000c01v1Entry 25 }

		-- 1.3.6.1.4.1.10106.3.101291.1.1.27
		vtr2000c01v1IpAdd0 OBJECT-TYPE
			SYNTAX Uint8
			MAX-ACCESS read-write
			STATUS current
			DESCRIPTION
				"Unicast IP address (0)"
		::= { vtr2000c01v1Entry 27 }

		-- 1.3.6.1.4.1.10106.3.101291.1.1.29
		vtr2000c01v1IpAdd1 OBJECT-TYPE
			SYNTAX Uint8
			MAX-ACCESS read-write
			STATUS current
			DESCRIPTION
				"Unicast IP address (1)"
		::= { vtr2000c01v1Entry 29 }

		-- 1.3.6.1.4.1.10106.3.101291.1.1.31
		vtr2000c01v1IpAdd2 OBJECT-TYPE
			SYNTAX Uint8
			MAX-ACCESS read-write
			STATUS current
			DESCRIPTION
				"Unicast IP address (2)"
		::= { vtr2000c01v1Entry 31 }

		-- 1.3.6.1.4.1.10106.3.101291.1.1.33
		vtr2000c01v1IpAdd3 OBJECT-TYPE
			SYNTAX Uint8
			MAX-ACCESS read-write
			STATUS current
			DESCRIPTION
				"Unicast IP address (3)"
		::= { vtr2000c01v1Entry 33 }

		-- 1.3.6.1.4.1.10106.3.101291.1.1.35
		vtr2000c01v1IpMask0 OBJECT-TYPE
			SYNTAX Uint8
			MAX-ACCESS read-write
			STATUS current
			DESCRIPTION
				"IP mask (0)"
		::= { vtr2000c01v1Entry 35 }

		-- 1.3.6.1.4.1.10106.3.101291.1.1.37
		vtr2000c01v1IpMask1 OBJECT-TYPE
			SYNTAX Uint8
			MAX-ACCESS read-write
			STATUS current
			DESCRIPTION
				"IP mask (1)"
		::= { vtr2000c01v1Entry 37 }

		-- 1.3.6.1.4.1.10106.3.101291.1.1.39
		vtr2000c01v1IpMask2 OBJECT-TYPE
			SYNTAX Uint8
			MAX-ACCESS read-write
			STATUS current
			DESCRIPTION
				"IP mask (2)"
		::= { vtr2000c01v1Entry 39 }

		-- 1.3.6.1.4.1.10106.3.101291.1.1.41
		vtr2000c01v1IpMask3 OBJECT-TYPE
			SYNTAX Uint8
			MAX-ACCESS read-write
			STATUS current
			DESCRIPTION
				"IP mask (3)"
		::= { vtr2000c01v1Entry 41 }

		-- 1.3.6.1.4.1.10106.3.101291.1.1.43
		vtr2000c01v1IpGway0 OBJECT-TYPE
			SYNTAX Uint8
			MAX-ACCESS read-write
			STATUS current
			DESCRIPTION
				"Gateway IP address (0)"
		::= { vtr2000c01v1Entry 43 }

		-- 1.3.6.1.4.1.10106.3.101291.1.1.45
		vtr2000c01v1IpGway1 OBJECT-TYPE
			SYNTAX Uint8
			MAX-ACCESS read-write
			STATUS current
			DESCRIPTION
				"Gateway IP address (1)"
		::= { vtr2000c01v1Entry 45 }

		-- 1.3.6.1.4.1.10106.3.101291.1.1.47
		vtr2000c01v1IpGway2 OBJECT-TYPE
			SYNTAX Uint8
			MAX-ACCESS read-write
			STATUS current
			DESCRIPTION
				"Gateway IP address (2)"
		::= { vtr2000c01v1Entry 47 }

		-- 1.3.6.1.4.1.10106.3.101291.1.1.49
		vtr2000c01v1IpGway3 OBJECT-TYPE
			SYNTAX Uint8
			MAX-ACCESS read-write
			STATUS current
			DESCRIPTION
				"Gateway IP address (3)"
		::= { vtr2000c01v1Entry 49 }

		-- 1.3.6.1.4.1.10106.3.101291.1.1.51
		vtr2000c01v1NtpIpAddress0 OBJECT-TYPE
			SYNTAX Uint8
			MAX-ACCESS read-write
			STATUS current
			DESCRIPTION
				"NTP server IP address (0)"
		::= { vtr2000c01v1Entry 51 }

		-- 1.3.6.1.4.1.10106.3.101291.1.1.53
		vtr2000c01v1NtpIpAddress1 OBJECT-TYPE
			SYNTAX Uint8
			MAX-ACCESS read-write
			STATUS current
			DESCRIPTION
				"NTP server IP address (1)"
		::= { vtr2000c01v1Entry 53 }

		-- 1.3.6.1.4.1.10106.3.101291.1.1.55
		vtr2000c01v1NtpIpAddress2 OBJECT-TYPE
			SYNTAX Uint8
			MAX-ACCESS read-write
			STATUS current
			DESCRIPTION
				"NTP server IP address (2)"
		::= { vtr2000c01v1Entry 55 }

		-- 1.3.6.1.4.1.10106.3.101291.1.1.57
		vtr2000c01v1NtpIpAddress3 OBJECT-TYPE
			SYNTAX Uint8
			MAX-ACCESS read-write
			STATUS current
			DESCRIPTION
				"NTP server IP address (3)"
		::= { vtr2000c01v1Entry 57 }

		-- 1.3.6.1.4.1.10106.3.101291.1.1.59
		vtr2000c01v1Measure OBJECT-TYPE
			SYNTAX TimeX1MsInt32
			MAX-ACCESS read-only
			STATUS current
			DESCRIPTION
				"Difference between IN1 and IN2 or timestamp"
		::= { vtr2000c01v1Entry 59 }

		-- 1.3.6.1.4.1.10106.3.101291.1.1.61
		vtr2000c01v1Format1 OBJECT-TYPE
			SYNTAX SdiHd3gFmt3
			MAX-ACCESS read-only
			STATUS current
			DESCRIPTION
				"IN1 input format"
		::= { vtr2000c01v1Entry 61 }

		-- 1.3.6.1.4.1.10106.3.101291.1.1.63
		vtr2000c01v1SdiInvalid1 OBJECT-TYPE
			SYNTAX BitFail
			MAX-ACCESS read-only
			STATUS current
			DESCRIPTION
				"SDI signal not valid in input IN1"
		::= { vtr2000c01v1Entry 63 }

		-- 1.3.6.1.4.1.10106.3.101291.1.1.65
		vtr2000c01v1NoSignal1 OBJECT-TYPE
			SYNTAX BitFail
			MAX-ACCESS read-only
			STATUS current
			DESCRIPTION
				"No signal detected in input IN1"
		::= { vtr2000c01v1Entry 65 }

		-- 1.3.6.1.4.1.10106.3.101291.1.1.67
		vtr2000c01v1CrcErr1 OBJECT-TYPE
			SYNTAX BitFail
			MAX-ACCESS read-only
			STATUS current
			DESCRIPTION
				"IN1 CRC/EDH fail"
		::= { vtr2000c01v1Entry 67 }

		-- 1.3.6.1.4.1.10106.3.101291.1.1.69
		vtr2000c01v1TcSrcFail1 OBJECT-TYPE
			SYNTAX BitFail
			MAX-ACCESS read-only
			STATUS current
			DESCRIPTION
				"Selected timecode source not present in IN1 input"
		::= { vtr2000c01v1Entry 69 }

		-- 1.3.6.1.4.1.10106.3.101291.1.1.71
		vtr2000c01v1AtcVitcPres1 OBJECT-TYPE
			SYNTAX BitFailN
			MAX-ACCESS read-only
			STATUS current
			DESCRIPTION
				"ATC-VITC present in IN1"
		::= { vtr2000c01v1Entry 71 }

		-- 1.3.6.1.4.1.10106.3.101291.1.1.73
		vtr2000c01v1AtcLtcPres1 OBJECT-TYPE
			SYNTAX BitFailN
			MAX-ACCESS read-only
			STATUS current
			DESCRIPTION
				"ATC-LTC present in IN1"
		::= { vtr2000c01v1Entry 73 }

		-- 1.3.6.1.4.1.10106.3.101291.1.1.75
		vtr2000c01v1DvitcPres1 OBJECT-TYPE
			SYNTAX BitFailN
			MAX-ACCESS read-only
			STATUS current
			DESCRIPTION
				"DVITC present in IN1"
		::= { vtr2000c01v1Entry 75 }

		-- 1.3.6.1.4.1.10106.3.101291.1.1.77
		vtr2000c01v1LtcEmbPres1 OBJECT-TYPE
			SYNTAX BitFailN
			MAX-ACCESS read-only
			STATUS current
			DESCRIPTION
				"Embedded LTC present in SDI IN1 in the selected audio channel"
		::= { vtr2000c01v1Entry 77 }

		-- 1.3.6.1.4.1.10106.3.101291.1.1.79
		vtr2000c01v1AudGrpPres11 OBJECT-TYPE
			SYNTAX BitFailN
			MAX-ACCESS read-only
			STATUS current
			DESCRIPTION
				"Audio group presence in SDI input"
		::= { vtr2000c01v1Entry 79 }

		-- 1.3.6.1.4.1.10106.3.101291.1.1.81
		vtr2000c01v1AudGrpPres12 OBJECT-TYPE
			SYNTAX BitFailN
			MAX-ACCESS read-only
			STATUS current
			DESCRIPTION
				"Audio group presence in SDI input"
		::= { vtr2000c01v1Entry 81 }

		-- 1.3.6.1.4.1.10106.3.101291.1.1.83
		vtr2000c01v1AudGrpPres13 OBJECT-TYPE
			SYNTAX BitFailN
			MAX-ACCESS read-only
			STATUS current
			DESCRIPTION
				"Audio group presence in SDI input"
		::= { vtr2000c01v1Entry 83 }

		-- 1.3.6.1.4.1.10106.3.101291.1.1.85
		vtr2000c01v1AudGrpPres14 OBJECT-TYPE
			SYNTAX BitFailN
			MAX-ACCESS read-only
			STATUS current
			DESCRIPTION
				"Audio group presence in SDI input"
		::= { vtr2000c01v1Entry 85 }

		-- 1.3.6.1.4.1.10106.3.101291.1.1.87
		vtr2000c01v1Format2 OBJECT-TYPE
			SYNTAX SdiHd3gFmt3
			MAX-ACCESS read-only
			STATUS current
			DESCRIPTION
				"IN2 input format"
		::= { vtr2000c01v1Entry 87 }

		-- 1.3.6.1.4.1.10106.3.101291.1.1.89
		vtr2000c01v1SdiInvalid2 OBJECT-TYPE
			SYNTAX BitFail
			MAX-ACCESS read-only
			STATUS current
			DESCRIPTION
				"SDI signal not valid in input IN2"
		::= { vtr2000c01v1Entry 89 }

		-- 1.3.6.1.4.1.10106.3.101291.1.1.91
		vtr2000c01v1NoSignal2 OBJECT-TYPE
			SYNTAX BitFail
			MAX-ACCESS read-only
			STATUS current
			DESCRIPTION
				"No signal detected in input IN2"
		::= { vtr2000c01v1Entry 91 }

		-- 1.3.6.1.4.1.10106.3.101291.1.1.93
		vtr2000c01v1CrcErr2 OBJECT-TYPE
			SYNTAX BitFail
			MAX-ACCESS read-only
			STATUS current
			DESCRIPTION
				"IN2 CRC/EDH fail"
		::= { vtr2000c01v1Entry 93 }

		-- 1.3.6.1.4.1.10106.3.101291.1.1.95
		vtr2000c01v1TcSrcFail2 OBJECT-TYPE
			SYNTAX BitFail
			MAX-ACCESS read-only
			STATUS current
			DESCRIPTION
				"Selected timecode source not present in input"
		::= { vtr2000c01v1Entry 95 }

		-- 1.3.6.1.4.1.10106.3.101291.1.1.97
		vtr2000c01v1AtcVitcPres2 OBJECT-TYPE
			SYNTAX BitFailN
			MAX-ACCESS read-only
			STATUS current
			DESCRIPTION
				"ATC-VITC present in IN2"
		::= { vtr2000c01v1Entry 97 }

		-- 1.3.6.1.4.1.10106.3.101291.1.1.99
		vtr2000c01v1AtcLtcPres2 OBJECT-TYPE
			SYNTAX BitFailN
			MAX-ACCESS read-only
			STATUS current
			DESCRIPTION
				"ATC-LTC present in IN2"
		::= { vtr2000c01v1Entry 99 }

		-- 1.3.6.1.4.1.10106.3.101291.1.1.101
		vtr2000c01v1DvitcPres2 OBJECT-TYPE
			SYNTAX BitFailN
			MAX-ACCESS read-only
			STATUS current
			DESCRIPTION
				"DVITC present in IN2"
		::= { vtr2000c01v1Entry 101 }

		-- 1.3.6.1.4.1.10106.3.101291.1.1.103
		vtr2000c01v1LtcEmbPres2 OBJECT-TYPE
			SYNTAX BitFailN
			MAX-ACCESS read-only
			STATUS current
			DESCRIPTION
				"Embedded LTC present in SDI IN2 in the selected audio channel"
		::= { vtr2000c01v1Entry 103 }

		-- 1.3.6.1.4.1.10106.3.101291.1.1.105
		vtr2000c01v1AudGrpPres21 OBJECT-TYPE
			SYNTAX BitFailN
			MAX-ACCESS read-only
			STATUS current
			DESCRIPTION
				"Audio group presence in SDI input"
		::= { vtr2000c01v1Entry 105 }

		-- 1.3.6.1.4.1.10106.3.101291.1.1.107
		vtr2000c01v1AudGrpPres22 OBJECT-TYPE
			SYNTAX BitFailN
			MAX-ACCESS read-only
			STATUS current
			DESCRIPTION
				"Audio group presence in SDI input"
		::= { vtr2000c01v1Entry 107 }

		-- 1.3.6.1.4.1.10106.3.101291.1.1.109
		vtr2000c01v1AudGrpPres23 OBJECT-TYPE
			SYNTAX BitFailN
			MAX-ACCESS read-only
			STATUS current
			DESCRIPTION
				"Audio group presence in SDI input"
		::= { vtr2000c01v1Entry 109 }

		-- 1.3.6.1.4.1.10106.3.101291.1.1.111
		vtr2000c01v1AudGrpPres24 OBJECT-TYPE
			SYNTAX BitFailN
			MAX-ACCESS read-only
			STATUS current
			DESCRIPTION
				"Audio group presence in SDI input"
		::= { vtr2000c01v1Entry 111 }

		-- 1.3.6.1.4.1.10106.3.101291.1.1.113
		vtr2000c01v1LtcInFail OBJECT-TYPE
			SYNTAX BitFail
			MAX-ACCESS read-only
			STATUS current
			DESCRIPTION
				"LTC signal not detected in LTC I/O terminals"
		::= { vtr2000c01v1Entry 113 }

		-- 1.3.6.1.4.1.10106.3.101291.1.1.115
		vtr2000c01v1BusRefFail OBJECT-TYPE
			SYNTAX BitFail
			MAX-ACCESS read-only
			STATUS current
			DESCRIPTION
				"13.5 MHz reference signal not present in backplane bus"
		::= { vtr2000c01v1Entry 115 }

		-- 1.3.6.1.4.1.10106.3.101291.1.1.117
		vtr2000c01v1LockSrc OBJECT-TYPE
			SYNTAX VtrLockSrc
			MAX-ACCESS read-only
			STATUS current
			DESCRIPTION
				"Lock source in use"
		::= { vtr2000c01v1Entry 117 }

		-- 1.3.6.1.4.1.10106.3.101291.1.1.119
		vtr2000c01v1MeasRdy OBJECT-TYPE
			SYNTAX BitFailN
			MAX-ACCESS read-only
			STATUS current
			DESCRIPTION
				"Indicates whether the timecode inputs involved in the measurement are valid and available"
		::= { vtr2000c01v1Entry 119 }

		-- 1.3.6.1.4.1.10106.3.101291.1.1.121
		vtr2000c01v1EthLink OBJECT-TYPE
			SYNTAX Ipa2EtherStat
			MAX-ACCESS read-only
			STATUS current
			DESCRIPTION
				"Ethernet conection status"
		::= { vtr2000c01v1Entry 121 }

		-- 1.3.6.1.4.1.10106.3.101291.1.1.123
		vtr2000c01v1EthSystem OBJECT-TYPE
			SYNTAX Ipa2EtherSys
			MAX-ACCESS read-only
			STATUS current
			DESCRIPTION
				"Ethernet conection system"
		::= { vtr2000c01v1Entry 123 }

		-- 1.3.6.1.4.1.10106.3.101291.1.1.125
		vtr2000c01v1SerialNo OBJECT-TYPE
			SYNTAX SerialNo
			MAX-ACCESS read-only
			STATUS current
			DESCRIPTION
				"Serial number"
		::= { vtr2000c01v1Entry 125 }

		-- 1.3.6.1.4.1.10106.3.616301
		gpd2000c01v1 OBJECT IDENTIFIER ::= { albalaProducts 616301 }

		-- 1.3.6.1.4.1.10106.3.616301.1
		gpd2000c01v1Table  OBJECT-TYPE
			SYNTAX SEQUENCE OF Gpd2000c01v1Entry
			MAX-ACCESS not-accessible
			STATUS current
			DESCRIPTION
				"Module  GPD2000C01V1 Table"
			::= { gpd2000c01v1 1 }

		-- 1.3.6.1.4.1.10106.3.616301.1.1
		gpd2000c01v1Entry  OBJECT-TYPE
			SYNTAX Gpd2000c01v1Entry
			MAX-ACCESS not-accessible
			STATUS current
			DESCRIPTION
				"Module GPD2000C01V1 Entry"
			INDEX { gpd2000c01v1Index }
			::= { gpd2000c01v1Table 1 }

			Gpd2000c01v1Entry ::=
			SEQUENCE {
				gpd2000c01v1Index
				ModuleIndex,
				gpd2000c01v1VccGnssLow
				GpdVoltage,
				gpd2000c01v1IccAntennaLow
				GpdCurrent,
				gpd2000c01v1IccAntennaHigh
				GpdCurrent,
				gpd2000c01v1VccGnss1Fail
				BitFail,
				gpd2000c01v1VccGnss1FailTrapEnable
				AlarmEnable,
				gpd2000c01v1VccGnss2Fail
				BitFail,
				gpd2000c01v1VccGnss2FailTrapEnable
				AlarmEnable,
				gpd2000c01v1VccGnss3Fail
				BitFail,
				gpd2000c01v1VccGnss3FailTrapEnable
				AlarmEnable,
				gpd2000c01v1VccGnss4Fail
				BitFail,
				gpd2000c01v1VccGnss4FailTrapEnable
				AlarmEnable,
				gpd2000c01v1VccAntennaFail
				BitFail,
				gpd2000c01v1VccAntennaFailTrapEnable
				AlarmEnable,
				gpd2000c01v1IccAntennaFail
				BitFail,
				gpd2000c01v1IccAntennaFailTrapEnable
				AlarmEnable,
				gpd2000c01v1NoAntenna
				BitFail,
				gpd2000c01v1NoAntennaTrapEnable
				AlarmEnable,
				gpd2000c01v1DcGnss1
				GpdVoltage,
				gpd2000c01v1DcGnss2
				GpdVoltage,
				gpd2000c01v1DcGnss3
				GpdVoltage,
				gpd2000c01v1DcGnss4
				GpdVoltage,
				gpd2000c01v1AntennaVcc
				GpdVoltage,
				gpd2000c01v1AntennaIcc
				GpdCurrent,
				gpd2000c01v1SerialNo
				SerialNo
			 }

		-- 1.3.6.1.4.1.10106.3.101291.1.1.1
		gpd2000c01v1Index OBJECT-TYPE
			SYNTAX ModuleIndex
			MAX-ACCESS read-only
			STATUS current
			DESCRIPTION
				"Index of GPD2000C01V1 Table"
		::= { gpd2000c01v1Entry 1 }

		-- 1.3.6.1.4.1.10106.3.101291.1.1.3
		gpd2000c01v1VccGnssLow OBJECT-TYPE
			SYNTAX GpdVoltage
			MAX-ACCESS read-write
			STATUS current
			DESCRIPTION
				"VCC low threshold"
		::= { gpd2000c01v1Entry 3 }

		-- 1.3.6.1.4.1.10106.3.101291.1.1.5
		gpd2000c01v1IccAntennaLow OBJECT-TYPE
			SYNTAX GpdCurrent
			MAX-ACCESS read-write
			STATUS current
			DESCRIPTION
				"ICC low threshold"
		::= { gpd2000c01v1Entry 5 }

		-- 1.3.6.1.4.1.10106.3.101291.1.1.7
		gpd2000c01v1IccAntennaHigh OBJECT-TYPE
			SYNTAX GpdCurrent
			MAX-ACCESS read-write
			STATUS current
			DESCRIPTION
				"ICC high threshold"
		::= { gpd2000c01v1Entry 7 }

		-- 1.3.6.1.4.1.10106.3.101291.1.1.9
		gpd2000c01v1VccGnss1Fail OBJECT-TYPE
			SYNTAX BitFail
			MAX-ACCESS read-only
			STATUS current
			DESCRIPTION
				"VCC GNSS Input 1 fail"
		::= { gpd2000c01v1Entry 9 }

		-- 1.3.6.1.4.1.10106.3.101291.1.1.10
		gpd2000c01v1VccGnss1FailTrapEnable OBJECT-TYPE
			SYNTAX AlarmEnable
			MAX-ACCESS read-write
			STATUS current
			DESCRIPTION
				"VCC GNSS Input 1 fail Trap Enable"
		::= { gpd2000c01v1Entry 10 }

		-- 1.3.6.1.4.1.10106.3.101291.1.1.11
		gpd2000c01v1VccGnss2Fail OBJECT-TYPE
			SYNTAX BitFail
			MAX-ACCESS read-only
			STATUS current
			DESCRIPTION
				"VCC GNSS Input 2 fail"
		::= { gpd2000c01v1Entry 11 }

		-- 1.3.6.1.4.1.10106.3.101291.1.1.12
		gpd2000c01v1VccGnss2FailTrapEnable OBJECT-TYPE
			SYNTAX AlarmEnable
			MAX-ACCESS read-write
			STATUS current
			DESCRIPTION
				"VCC GNSS Input 2 fail Trap Enable"
		::= { gpd2000c01v1Entry 12 }

		-- 1.3.6.1.4.1.10106.3.101291.1.1.13
		gpd2000c01v1VccGnss3Fail OBJECT-TYPE
			SYNTAX BitFail
			MAX-ACCESS read-only
			STATUS current
			DESCRIPTION
				"VCC GNSS Input 3 fail"
		::= { gpd2000c01v1Entry 13 }

		-- 1.3.6.1.4.1.10106.3.101291.1.1.14
		gpd2000c01v1VccGnss3FailTrapEnable OBJECT-TYPE
			SYNTAX AlarmEnable
			MAX-ACCESS read-write
			STATUS current
			DESCRIPTION
				"VCC GNSS Input 3 fail Trap Enable"
		::= { gpd2000c01v1Entry 14 }

		-- 1.3.6.1.4.1.10106.3.101291.1.1.15
		gpd2000c01v1VccGnss4Fail OBJECT-TYPE
			SYNTAX BitFail
			MAX-ACCESS read-only
			STATUS current
			DESCRIPTION
				"VCC GNSS Input 4 fail"
		::= { gpd2000c01v1Entry 15 }

		-- 1.3.6.1.4.1.10106.3.101291.1.1.16
		gpd2000c01v1VccGnss4FailTrapEnable OBJECT-TYPE
			SYNTAX AlarmEnable
			MAX-ACCESS read-write
			STATUS current
			DESCRIPTION
				"VCC GNSS Input 4 fail Trap Enable"
		::= { gpd2000c01v1Entry 16 }

		-- 1.3.6.1.4.1.10106.3.101291.1.1.17
		gpd2000c01v1VccAntennaFail OBJECT-TYPE
			SYNTAX BitFail
			MAX-ACCESS read-only
			STATUS current
			DESCRIPTION
				"VCC antenna fail"
		::= { gpd2000c01v1Entry 17 }

		-- 1.3.6.1.4.1.10106.3.101291.1.1.18
		gpd2000c01v1VccAntennaFailTrapEnable OBJECT-TYPE
			SYNTAX AlarmEnable
			MAX-ACCESS read-write
			STATUS current
			DESCRIPTION
				"VCC antenna fail Trap Enable"
		::= { gpd2000c01v1Entry 18 }

		-- 1.3.6.1.4.1.10106.3.101291.1.1.19
		gpd2000c01v1IccAntennaFail OBJECT-TYPE
			SYNTAX BitFail
			MAX-ACCESS read-only
			STATUS current
			DESCRIPTION
				"ICC antenna fail"
		::= { gpd2000c01v1Entry 19 }

		-- 1.3.6.1.4.1.10106.3.101291.1.1.20
		gpd2000c01v1IccAntennaFailTrapEnable OBJECT-TYPE
			SYNTAX AlarmEnable
			MAX-ACCESS read-write
			STATUS current
			DESCRIPTION
				"ICC antenna fail Trap Enable"
		::= { gpd2000c01v1Entry 20 }

		-- 1.3.6.1.4.1.10106.3.101291.1.1.21
		gpd2000c01v1NoAntenna OBJECT-TYPE
			SYNTAX BitFail
			MAX-ACCESS read-only
			STATUS current
			DESCRIPTION
				"Antenna presence fail"
		::= { gpd2000c01v1Entry 21 }

		-- 1.3.6.1.4.1.10106.3.101291.1.1.22
		gpd2000c01v1NoAntennaTrapEnable OBJECT-TYPE
			SYNTAX AlarmEnable
			MAX-ACCESS read-write
			STATUS current
			DESCRIPTION
				"Antenna presence fail Trap Enable"
		::= { gpd2000c01v1Entry 22 }

		-- 1.3.6.1.4.1.10106.3.101291.1.1.23
		gpd2000c01v1DcGnss1 OBJECT-TYPE
			SYNTAX GpdVoltage
			MAX-ACCESS read-only
			STATUS current
			DESCRIPTION
				"VCC GNSS Input 1"
		::= { gpd2000c01v1Entry 23 }

		-- 1.3.6.1.4.1.10106.3.101291.1.1.25
		gpd2000c01v1DcGnss2 OBJECT-TYPE
			SYNTAX GpdVoltage
			MAX-ACCESS read-only
			STATUS current
			DESCRIPTION
				"VCC GNSS Input 2"
		::= { gpd2000c01v1Entry 25 }

		-- 1.3.6.1.4.1.10106.3.101291.1.1.27
		gpd2000c01v1DcGnss3 OBJECT-TYPE
			SYNTAX GpdVoltage
			MAX-ACCESS read-only
			STATUS current
			DESCRIPTION
				"VCC GNSS Input 3"
		::= { gpd2000c01v1Entry 27 }

		-- 1.3.6.1.4.1.10106.3.101291.1.1.29
		gpd2000c01v1DcGnss4 OBJECT-TYPE
			SYNTAX GpdVoltage
			MAX-ACCESS read-only
			STATUS current
			DESCRIPTION
				"VCC GNSS Input 4"
		::= { gpd2000c01v1Entry 29 }

		-- 1.3.6.1.4.1.10106.3.101291.1.1.31
		gpd2000c01v1AntennaVcc OBJECT-TYPE
			SYNTAX GpdVoltage
			MAX-ACCESS read-only
			STATUS current
			DESCRIPTION
				"Antenna supply VCC"
		::= { gpd2000c01v1Entry 31 }

		-- 1.3.6.1.4.1.10106.3.101291.1.1.33
		gpd2000c01v1AntennaIcc OBJECT-TYPE
			SYNTAX GpdCurrent
			MAX-ACCESS read-only
			STATUS current
			DESCRIPTION
				"Antenna supply ICC"
		::= { gpd2000c01v1Entry 33 }

		-- 1.3.6.1.4.1.10106.3.101291.1.1.35
		gpd2000c01v1SerialNo OBJECT-TYPE
			SYNTAX SerialNo
			MAX-ACCESS read-only
			STATUS current
			DESCRIPTION
				"Serial number"
		::= { gpd2000c01v1Entry 35 }

		-- 1.3.6.1.4.1.10106.3.620401
		hxc2000c02v1 OBJECT IDENTIFIER ::= { albalaProducts 620401 }

		-- 1.3.6.1.4.1.10106.3.620401.1
		hxc2000c02v1Table  OBJECT-TYPE
			SYNTAX SEQUENCE OF Hxc2000c02v1Entry
			MAX-ACCESS not-accessible
			STATUS current
			DESCRIPTION
				"Module  HXC2000C02V1 Table"
			::= { hxc2000c02v1 1 }

		-- 1.3.6.1.4.1.10106.3.620401.1.1
		hxc2000c02v1Entry  OBJECT-TYPE
			SYNTAX Hxc2000c02v1Entry
			MAX-ACCESS not-accessible
			STATUS current
			DESCRIPTION
				"Module HXC2000C02V1 Entry"
			INDEX { hxc2000c02v1Index }
			::= { hxc2000c02v1Table 1 }

			Hxc2000c02v1Entry ::=
			SEQUENCE {
				hxc2000c02v1Index
				ModuleIndex,
				hxc2000c02v1ActivePreset
				Preset16Active,
				hxc2000c02v1LoadPreset
				Preset16Load,
				hxc2000c02v1SavePreset
				Preset16Save,
				hxc2000c02v1AnaRefFmt
				SdiHd3gFmt6,
				hxc2000c02v1AnaRefFmtTrapEnable
				AlarmEnable,
				hxc2000c02v1GenlockMode
				GenlockM0de2,
				hxc2000c02v1EnaAud20Bit
				Bit0Yes1No,
				hxc2000c02v1FailMode
				Bit0Fre1Blk,
				hxc2000c02v1ModeConv
				Bit0Aut1Man,
				hxc2000c02v1ModeConvTrapEnable
				AlarmEnable,
				hxc2000c02v1OutAfd
				Afd1,
				hxc2000c02v1OutAfdTrapEnable
				AlarmEnable,
				hxc2000c02v1OutCf
				Cf1,
				hxc2000c02v1OutCfTrapEnable
				AlarmEnable,
				hxc2000c02v1Esc11
				BitMask,
				hxc2000c02v1InAfdExpct
				Afd1,
				hxc2000c02v1InAfdExpctTrapEnable
				AlarmEnable,
				hxc2000c02v1InCfExpct
				Cf1,
				hxc2000c02v1InCfExpctTrapEnable
				AlarmEnable,
				hxc2000c02v1TxFmt
				SdiHd12gFmt4,
				hxc2000c02v1TxFmtTrapEnable
				AlarmEnable,
				hxc2000c02v1DeintAlgorithm
				DeintAlgorithm,
				hxc2000c02v1DeintAlgorithmTrapEnable
				AlarmEnable,
				hxc2000c02v1OutEnaS2016
				Bit0No1Yes,
				hxc2000c02v1OutEnaVii
				Bit0No1Yes,
				hxc2000c02v1OutEnaWss
				Bit0No1Yes,
				hxc2000c02v1OutEnaVitc
				Bit0No1Yes,
				hxc2000c02v1OutEnaAtc
				Bit0No1Yes,
				hxc2000c02v1OutEnaTxt
				Bit0No1Yes,
				hxc2000c02v1OutEnaCea608
				Bit0No1Yes,
				hxc2000c02v1VDelay
				DelayLines3,
				hxc2000c02v1HDelay
				DelayPixel6,
				hxc2000c02v1Grp1P0Gain
				Gain24dbMute,
				hxc2000c02v1Grp1P0Phase
				Bit0Nor1Inv,
				hxc2000c02v1Grp1P1Gain
				Gain24dbMute,
				hxc2000c02v1Grp1P1Phase
				Bit0Nor1Inv,
				hxc2000c02v1Grp2P0Gain
				Gain24dbMute,
				hxc2000c02v1Grp2P0Phase
				Bit0Nor1Inv,
				hxc2000c02v1Grp2P1Gain
				Gain24dbMute,
				hxc2000c02v1Grp2P1Phase
				Bit0Nor1Inv,
				hxc2000c02v1Grp3P0Gain
				Gain24dbMute,
				hxc2000c02v1Grp3P0Phase
				Bit0Nor1Inv,
				hxc2000c02v1Grp3P1Gain
				Gain24dbMute,
				hxc2000c02v1Grp3P1Phase
				Bit0Nor1Inv,
				hxc2000c02v1Grp4P0Gain
				Gain24dbMute,
				hxc2000c02v1Grp4P0Phase
				Bit0Nor1Inv,
				hxc2000c02v1Grp4P1Gain
				Gain24dbMute,
				hxc2000c02v1Grp4P1Phase
				Bit0Nor1Inv,
				hxc2000c02v1MuteEna
				Bit0No1Yes,
				hxc2000c02v1StatFlash
				BitFailN,
				hxc2000c02v1InPhyFail
				BitFail,
				hxc2000c02v1InPhyFailTrapEnable
				AlarmEnable,
				hxc2000c02v1InFmtFail
				BitFail,
				hxc2000c02v1InFmtFailTrapEnable
				AlarmEnable,
				hxc2000c02v1InIncFail
				BitFail,
				hxc2000c02v1InIncFailTrapEnable
				AlarmEnable,
				hxc2000c02v1InPresCrcFail
				BitFail,
				hxc2000c02v1InCrcFail
				BitFail,
				hxc2000c02v1InCrcFailTrapEnable
				AlarmEnable,
				hxc2000c02v1InPrsS352Fail
				BitFail,
				hxc2000c02v1InS352Fail
				BitFail,
				hxc2000c02v1PresS2016Fail
				BitFail,
				hxc2000c02v1ErrS2016Fail
				BitFail,
				hxc2000c02v1PresAudG1Fail
				BitFail,
				hxc2000c02v1PresAudG1FailTrapEnable
				AlarmEnable,
				hxc2000c02v1PresAudG2Fail
				BitFail,
				hxc2000c02v1PresAudG2FailTrapEnable
				AlarmEnable,
				hxc2000c02v1PresAudG3Fail
				BitFail,
				hxc2000c02v1PresAudG3FailTrapEnable
				AlarmEnable,
				hxc2000c02v1PresAudG4Fail
				BitFail,
				hxc2000c02v1PresAudG4FailTrapEnable
				AlarmEnable,
				hxc2000c02v1RefFail
				BitFail,
				hxc2000c02v1RefFailTrapEnable
				AlarmEnable,
				hxc2000c02v1RefFmtFail
				BitFail,
				hxc2000c02v1RefFmtFailTrapEnable
				AlarmEnable,
				hxc2000c02v1LockFail
				BitFail,
				hxc2000c02v1LockFailTrapEnable
				AlarmEnable,
				hxc2000c02v1UxcPres
				BitFail,
				hxc2000c02v1UxcPresTrapEnable
				AlarmEnable,
				hxc2000c02v1AudPair0Fail
				BitFail,
				hxc2000c02v1AudPair0FailTrapEnable
				AlarmEnable,
				hxc2000c02v1AudPair1Fail
				BitFail,
				hxc2000c02v1AudPair1FailTrapEnable
				AlarmEnable,
				hxc2000c02v1AudPair2Fail
				BitFail,
				hxc2000c02v1AudPair2FailTrapEnable
				AlarmEnable,
				hxc2000c02v1AudPair3Fail
				BitFail,
				hxc2000c02v1AudPair3FailTrapEnable
				AlarmEnable,
				hxc2000c02v1AudPair4Fail
				BitFail,
				hxc2000c02v1AudPair4FailTrapEnable
				AlarmEnable,
				hxc2000c02v1AudPair5Fail
				BitFail,
				hxc2000c02v1AudPair5FailTrapEnable
				AlarmEnable,
				hxc2000c02v1AudPair6Fail
				BitFail,
				hxc2000c02v1AudPair6FailTrapEnable
				AlarmEnable,
				hxc2000c02v1AudPair7Fail
				BitFail,
				hxc2000c02v1AudPair7FailTrapEnable
				AlarmEnable,
				hxc2000c02v1InAfdDetct
				Afd1,
				hxc2000c02v1InAfdDetctTrapEnable
				AlarmEnable,
				hxc2000c02v1InCfDetct
				Cf1,
				hxc2000c02v1InCfDetctTrapEnable
				AlarmEnable,
				hxc2000c02v1InFormat
				SdiHd12gFmt3,
				hxc2000c02v1InFormatTrapEnable
				AlarmEnable,
				hxc2000c02v1RefFormat
				SdiHd12gFmt3,
				hxc2000c02v1RefFormatTrapEnable
				AlarmEnable,
				hxc2000c02v1TxFormat
				SdiHd3gFmt3,
				hxc2000c02v1TxFormatTrapEnable
				AlarmEnable,
				hxc2000c02v1TxtPres
				BitFailN,
				hxc2000c02v1VitcPres
				BitFailN,
				hxc2000c02v1Mute
				Bit0No1Yes,
				hxc2000c02v1Black
				Bit0No1Yes,
				hxc2000c02v1Gpi1
				Bit0Off1On,
				hxc2000c02v1Gpi2
				Bit0Off1On,
				hxc2000c02v1Gpi3
				Bit0Off1On,
				hxc2000c02v1Gpi4
				Bit0Off1On,
				hxc2000c02v1SerialNo
				SerialNo
			 }

		-- 1.3.6.1.4.1.10106.3.101291.1.1.1
		hxc2000c02v1Index OBJECT-TYPE
			SYNTAX ModuleIndex
			MAX-ACCESS read-only
			STATUS current
			DESCRIPTION
				"Index of HXC2000C02V1 Table"
		::= { hxc2000c02v1Entry 1 }

		-- 1.3.6.1.4.1.10106.3.101291.1.1.3
		hxc2000c02v1ActivePreset OBJECT-TYPE
			SYNTAX Preset16Active
			MAX-ACCESS read-only
			STATUS current
			DESCRIPTION
				"Shows the active preset"
		::= { hxc2000c02v1Entry 3 }

		-- 1.3.6.1.4.1.10106.3.101291.1.1.5
		hxc2000c02v1LoadPreset OBJECT-TYPE
			SYNTAX Preset16Load
			MAX-ACCESS read-write
			STATUS current
			DESCRIPTION
				"Allows loading a preset"
		::= { hxc2000c02v1Entry 5 }

		-- 1.3.6.1.4.1.10106.3.101291.1.1.7
		hxc2000c02v1SavePreset OBJECT-TYPE
			SYNTAX Preset16Save
			MAX-ACCESS read-write
			STATUS current
			DESCRIPTION
				"Allows saving a preset"
		::= { hxc2000c02v1Entry 7 }

		-- 1.3.6.1.4.1.10106.3.101291.1.1.9
		hxc2000c02v1AnaRefFmt OBJECT-TYPE
			SYNTAX SdiHd3gFmt6
			MAX-ACCESS read-write
			STATUS current
			DESCRIPTION
				"Analog reference input format"
		::= { hxc2000c02v1Entry 9 }

		-- 1.3.6.1.4.1.10106.3.101291.1.1.10
		hxc2000c02v1AnaRefFmtTrapEnable OBJECT-TYPE
			SYNTAX AlarmEnable
			MAX-ACCESS read-write
			STATUS current
			DESCRIPTION
				"Analog reference input format Trap Enable"
		::= { hxc2000c02v1Entry 10 }

		-- 1.3.6.1.4.1.10106.3.101291.1.1.11
		hxc2000c02v1GenlockMode OBJECT-TYPE
			SYNTAX GenlockM0de2
			MAX-ACCESS read-write
			STATUS current
			DESCRIPTION
				"Allos selecting the reference input signal"
		::= { hxc2000c02v1Entry 11 }

		-- 1.3.6.1.4.1.10106.3.101291.1.1.13
		hxc2000c02v1EnaAud20Bit OBJECT-TYPE
			SYNTAX Bit0Yes1No
			MAX-ACCESS read-write
			STATUS current
			DESCRIPTION
				"Allows embedding 24-bit audio in SD signals"
		::= { hxc2000c02v1Entry 13 }

		-- 1.3.6.1.4.1.10106.3.101291.1.1.15
		hxc2000c02v1FailMode OBJECT-TYPE
			SYNTAX Bit0Fre1Blk
			MAX-ACCESS read-write
			STATUS current
			DESCRIPTION
				"Allows selecting the output video signal if the input fails"
		::= { hxc2000c02v1Entry 15 }

		-- 1.3.6.1.4.1.10106.3.101291.1.1.17
		hxc2000c02v1ModeConv OBJECT-TYPE
			SYNTAX Bit0Aut1Man
			MAX-ACCESS read-write
			STATUS current
			DESCRIPTION
				"Conversion mode"
		::= { hxc2000c02v1Entry 17 }

		-- 1.3.6.1.4.1.10106.3.101291.1.1.18
		hxc2000c02v1ModeConvTrapEnable OBJECT-TYPE
			SYNTAX AlarmEnable
			MAX-ACCESS read-write
			STATUS current
			DESCRIPTION
				"Conversion mode Trap Enable"
		::= { hxc2000c02v1Entry 18 }

		-- 1.3.6.1.4.1.10106.3.101291.1.1.19
		hxc2000c02v1OutAfd OBJECT-TYPE
			SYNTAX Afd1
			MAX-ACCESS read-write
			STATUS current
			DESCRIPTION
				"Output active format description"
		::= { hxc2000c02v1Entry 19 }

		-- 1.3.6.1.4.1.10106.3.101291.1.1.20
		hxc2000c02v1OutAfdTrapEnable OBJECT-TYPE
			SYNTAX AlarmEnable
			MAX-ACCESS read-write
			STATUS current
			DESCRIPTION
				"Output active format description Trap Enable"
		::= { hxc2000c02v1Entry 20 }

		-- 1.3.6.1.4.1.10106.3.101291.1.1.21
		hxc2000c02v1OutCf OBJECT-TYPE
			SYNTAX Cf1
			MAX-ACCESS read-write
			STATUS current
			DESCRIPTION
				"Output coded frame"
		::= { hxc2000c02v1Entry 21 }

		-- 1.3.6.1.4.1.10106.3.101291.1.1.22
		hxc2000c02v1OutCfTrapEnable OBJECT-TYPE
			SYNTAX AlarmEnable
			MAX-ACCESS read-write
			STATUS current
			DESCRIPTION
				"Output coded frame Trap Enable"
		::= { hxc2000c02v1Entry 22 }

		-- 1.3.6.1.4.1.10106.3.101291.1.1.23
		hxc2000c02v1Esc11 OBJECT-TYPE
			SYNTAX BitMask
			MAX-ACCESS read-write
			STATUS current
			DESCRIPTION
				"Enables the 1 to 1 scaling rate"
		::= { hxc2000c02v1Entry 23 }

		-- 1.3.6.1.4.1.10106.3.101291.1.1.25
		hxc2000c02v1InAfdExpct OBJECT-TYPE
			SYNTAX Afd1
			MAX-ACCESS read-write
			STATUS current
			DESCRIPTION
				"Input expected active format description"
		::= { hxc2000c02v1Entry 25 }

		-- 1.3.6.1.4.1.10106.3.101291.1.1.26
		hxc2000c02v1InAfdExpctTrapEnable OBJECT-TYPE
			SYNTAX AlarmEnable
			MAX-ACCESS read-write
			STATUS current
			DESCRIPTION
				"Input expected active format description Trap Enable"
		::= { hxc2000c02v1Entry 26 }

		-- 1.3.6.1.4.1.10106.3.101291.1.1.27
		hxc2000c02v1InCfExpct OBJECT-TYPE
			SYNTAX Cf1
			MAX-ACCESS read-write
			STATUS current
			DESCRIPTION
				"Input expected coded frame"
		::= { hxc2000c02v1Entry 27 }

		-- 1.3.6.1.4.1.10106.3.101291.1.1.28
		hxc2000c02v1InCfExpctTrapEnable OBJECT-TYPE
			SYNTAX AlarmEnable
			MAX-ACCESS read-write
			STATUS current
			DESCRIPTION
				"Input expected coded frame Trap Enable"
		::= { hxc2000c02v1Entry 28 }

		-- 1.3.6.1.4.1.10106.3.101291.1.1.29
		hxc2000c02v1TxFmt OBJECT-TYPE
			SYNTAX SdiHd12gFmt4
			MAX-ACCESS read-write
			STATUS current
			DESCRIPTION
				"Output format"
		::= { hxc2000c02v1Entry 29 }

		-- 1.3.6.1.4.1.10106.3.101291.1.1.30
		hxc2000c02v1TxFmtTrapEnable OBJECT-TYPE
			SYNTAX AlarmEnable
			MAX-ACCESS read-write
			STATUS current
			DESCRIPTION
				"Output format Trap Enable"
		::= { hxc2000c02v1Entry 30 }

		-- 1.3.6.1.4.1.10106.3.101291.1.1.31
		hxc2000c02v1DeintAlgorithm OBJECT-TYPE
			SYNTAX DeintAlgorithm
			MAX-ACCESS read-write
			STATUS current
			DESCRIPTION
				"Allows selecting the de-interlacing algorithm"
		::= { hxc2000c02v1Entry 31 }

		-- 1.3.6.1.4.1.10106.3.101291.1.1.32
		hxc2000c02v1DeintAlgorithmTrapEnable OBJECT-TYPE
			SYNTAX AlarmEnable
			MAX-ACCESS read-write
			STATUS current
			DESCRIPTION
				"Allows selecting the de-interlacing algorithm Trap Enable"
		::= { hxc2000c02v1Entry 32 }

		-- 1.3.6.1.4.1.10106.3.101291.1.1.33
		hxc2000c02v1OutEnaS2016 OBJECT-TYPE
			SYNTAX Bit0No1Yes
			MAX-ACCESS read-write
			STATUS current
			DESCRIPTION
				"Enables insertion of SMPTE 2016 packets in  OUT"
		::= { hxc2000c02v1Entry 33 }

		-- 1.3.6.1.4.1.10106.3.101291.1.1.35
		hxc2000c02v1OutEnaVii OBJECT-TYPE
			SYNTAX Bit0No1Yes
			MAX-ACCESS read-write
			STATUS current
			DESCRIPTION
				"Enables insertion of VII in OUT"
		::= { hxc2000c02v1Entry 35 }

		-- 1.3.6.1.4.1.10106.3.101291.1.1.37
		hxc2000c02v1OutEnaWss OBJECT-TYPE
			SYNTAX Bit0No1Yes
			MAX-ACCESS read-write
			STATUS current
			DESCRIPTION
				"Enables insertion of WSS in OUT"
		::= { hxc2000c02v1Entry 37 }

		-- 1.3.6.1.4.1.10106.3.101291.1.1.39
		hxc2000c02v1OutEnaVitc OBJECT-TYPE
			SYNTAX Bit0No1Yes
			MAX-ACCESS read-write
			STATUS current
			DESCRIPTION
				"Enables insertion of DVITC in OUT"
		::= { hxc2000c02v1Entry 39 }

		-- 1.3.6.1.4.1.10106.3.101291.1.1.41
		hxc2000c02v1OutEnaAtc OBJECT-TYPE
			SYNTAX Bit0No1Yes
			MAX-ACCESS read-write
			STATUS current
			DESCRIPTION
				"Enables insertion of ATC in OUT"
		::= { hxc2000c02v1Entry 41 }

		-- 1.3.6.1.4.1.10106.3.101291.1.1.43
		hxc2000c02v1OutEnaTxt OBJECT-TYPE
			SYNTAX Bit0No1Yes
			MAX-ACCESS read-write
			STATUS current
			DESCRIPTION
				"Enables insertion of TXT in OUT"
		::= { hxc2000c02v1Entry 43 }

		-- 1.3.6.1.4.1.10106.3.101291.1.1.45
		hxc2000c02v1OutEnaCea608 OBJECT-TYPE
			SYNTAX Bit0No1Yes
			MAX-ACCESS read-write
			STATUS current
			DESCRIPTION
				"Enables insertion of CEA608 modulation in OUT when format is 486I59.94 and CEA608 or CEA708 paquets are present"
		::= { hxc2000c02v1Entry 45 }

		-- 1.3.6.1.4.1.10106.3.101291.1.1.47
		hxc2000c02v1VDelay OBJECT-TYPE
			SYNTAX DelayLines3
			MAX-ACCESS read-write
			STATUS current
			DESCRIPTION
				"Allows adjusting the video vertical delay"
		::= { hxc2000c02v1Entry 47 }

		-- 1.3.6.1.4.1.10106.3.101291.1.1.49
		hxc2000c02v1HDelay OBJECT-TYPE
			SYNTAX DelayPixel6
			MAX-ACCESS read-write
			STATUS current
			DESCRIPTION
				"Allows adjusting the video horizontal delay"
		::= { hxc2000c02v1Entry 49 }

		-- 1.3.6.1.4.1.10106.3.101291.1.1.51
		hxc2000c02v1Grp1P0Gain OBJECT-TYPE
			SYNTAX Gain24dbMute
			MAX-ACCESS read-write
			STATUS current
			DESCRIPTION
				"Group 1 pair 0 gain"
		::= { hxc2000c02v1Entry 51 }

		-- 1.3.6.1.4.1.10106.3.101291.1.1.53
		hxc2000c02v1Grp1P0Phase OBJECT-TYPE
			SYNTAX Bit0Nor1Inv
			MAX-ACCESS read-write
			STATUS current
			DESCRIPTION
				"Group 1 pair 0 phase"
		::= { hxc2000c02v1Entry 53 }

		-- 1.3.6.1.4.1.10106.3.101291.1.1.55
		hxc2000c02v1Grp1P1Gain OBJECT-TYPE
			SYNTAX Gain24dbMute
			MAX-ACCESS read-write
			STATUS current
			DESCRIPTION
				"Group 1 pair 1 gain"
		::= { hxc2000c02v1Entry 55 }

		-- 1.3.6.1.4.1.10106.3.101291.1.1.57
		hxc2000c02v1Grp1P1Phase OBJECT-TYPE
			SYNTAX Bit0Nor1Inv
			MAX-ACCESS read-write
			STATUS current
			DESCRIPTION
				"Group 1 pair 1 phase"
		::= { hxc2000c02v1Entry 57 }

		-- 1.3.6.1.4.1.10106.3.101291.1.1.59
		hxc2000c02v1Grp2P0Gain OBJECT-TYPE
			SYNTAX Gain24dbMute
			MAX-ACCESS read-write
			STATUS current
			DESCRIPTION
				"Group 2 pair 0 gain"
		::= { hxc2000c02v1Entry 59 }

		-- 1.3.6.1.4.1.10106.3.101291.1.1.61
		hxc2000c02v1Grp2P0Phase OBJECT-TYPE
			SYNTAX Bit0Nor1Inv
			MAX-ACCESS read-write
			STATUS current
			DESCRIPTION
				"Group 2 pair 0 phase"
		::= { hxc2000c02v1Entry 61 }

		-- 1.3.6.1.4.1.10106.3.101291.1.1.63
		hxc2000c02v1Grp2P1Gain OBJECT-TYPE
			SYNTAX Gain24dbMute
			MAX-ACCESS read-write
			STATUS current
			DESCRIPTION
				"Group 2 pair 1 gain"
		::= { hxc2000c02v1Entry 63 }

		-- 1.3.6.1.4.1.10106.3.101291.1.1.65
		hxc2000c02v1Grp2P1Phase OBJECT-TYPE
			SYNTAX Bit0Nor1Inv
			MAX-ACCESS read-write
			STATUS current
			DESCRIPTION
				"Group 2 pair 1 phase"
		::= { hxc2000c02v1Entry 65 }

		-- 1.3.6.1.4.1.10106.3.101291.1.1.67
		hxc2000c02v1Grp3P0Gain OBJECT-TYPE
			SYNTAX Gain24dbMute
			MAX-ACCESS read-write
			STATUS current
			DESCRIPTION
				"Group 3 pair 0 gain"
		::= { hxc2000c02v1Entry 67 }

		-- 1.3.6.1.4.1.10106.3.101291.1.1.69
		hxc2000c02v1Grp3P0Phase OBJECT-TYPE
			SYNTAX Bit0Nor1Inv
			MAX-ACCESS read-write
			STATUS current
			DESCRIPTION
				"Group 3 pair 0 phase"
		::= { hxc2000c02v1Entry 69 }

		-- 1.3.6.1.4.1.10106.3.101291.1.1.71
		hxc2000c02v1Grp3P1Gain OBJECT-TYPE
			SYNTAX Gain24dbMute
			MAX-ACCESS read-write
			STATUS current
			DESCRIPTION
				"Group 3 pair 1 gain"
		::= { hxc2000c02v1Entry 71 }

		-- 1.3.6.1.4.1.10106.3.101291.1.1.73
		hxc2000c02v1Grp3P1Phase OBJECT-TYPE
			SYNTAX Bit0Nor1Inv
			MAX-ACCESS read-write
			STATUS current
			DESCRIPTION
				"Group 3 pair 1 phase"
		::= { hxc2000c02v1Entry 73 }

		-- 1.3.6.1.4.1.10106.3.101291.1.1.75
		hxc2000c02v1Grp4P0Gain OBJECT-TYPE
			SYNTAX Gain24dbMute
			MAX-ACCESS read-write
			STATUS current
			DESCRIPTION
				"Group 4 pair 0 gain"
		::= { hxc2000c02v1Entry 75 }

		-- 1.3.6.1.4.1.10106.3.101291.1.1.77
		hxc2000c02v1Grp4P0Phase OBJECT-TYPE
			SYNTAX Bit0Nor1Inv
			MAX-ACCESS read-write
			STATUS current
			DESCRIPTION
				"Group 4 pair 0 phase"
		::= { hxc2000c02v1Entry 77 }

		-- 1.3.6.1.4.1.10106.3.101291.1.1.79
		hxc2000c02v1Grp4P1Gain OBJECT-TYPE
			SYNTAX Gain24dbMute
			MAX-ACCESS read-write
			STATUS current
			DESCRIPTION
				"Group 4 pair 1 gain"
		::= { hxc2000c02v1Entry 79 }

		-- 1.3.6.1.4.1.10106.3.101291.1.1.81
		hxc2000c02v1Grp4P1Phase OBJECT-TYPE
			SYNTAX Bit0Nor1Inv
			MAX-ACCESS read-write
			STATUS current
			DESCRIPTION
				"Group 4 pair 1 phase"
		::= { hxc2000c02v1Entry 81 }

		-- 1.3.6.1.4.1.10106.3.101291.1.1.83
		hxc2000c02v1MuteEna OBJECT-TYPE
			SYNTAX Bit0No1Yes
			MAX-ACCESS read-write
			STATUS current
			DESCRIPTION
				"Enables outputs mute"
		::= { hxc2000c02v1Entry 83 }

		-- 1.3.6.1.4.1.10106.3.101291.1.1.85
		hxc2000c02v1StatFlash OBJECT-TYPE
			SYNTAX BitFailN
			MAX-ACCESS read-only
			STATUS current
			DESCRIPTION
				"Displays the Flash state"
		::= { hxc2000c02v1Entry 85 }

		-- 1.3.6.1.4.1.10106.3.101291.1.1.87
		hxc2000c02v1InPhyFail OBJECT-TYPE
			SYNTAX BitFail
			MAX-ACCESS read-only
			STATUS current
			DESCRIPTION
				"Absence fail"
		::= { hxc2000c02v1Entry 87 }

		-- 1.3.6.1.4.1.10106.3.101291.1.1.88
		hxc2000c02v1InPhyFailTrapEnable OBJECT-TYPE
			SYNTAX AlarmEnable
			MAX-ACCESS read-write
			STATUS current
			DESCRIPTION
				"Absence fail Trap Enable"
		::= { hxc2000c02v1Entry 88 }

		-- 1.3.6.1.4.1.10106.3.101291.1.1.89
		hxc2000c02v1InFmtFail OBJECT-TYPE
			SYNTAX BitFail
			MAX-ACCESS read-only
			STATUS current
			DESCRIPTION
				"Format fail"
		::= { hxc2000c02v1Entry 89 }

		-- 1.3.6.1.4.1.10106.3.101291.1.1.90
		hxc2000c02v1InFmtFailTrapEnable OBJECT-TYPE
			SYNTAX AlarmEnable
			MAX-ACCESS read-write
			STATUS current
			DESCRIPTION
				"Format fail Trap Enable"
		::= { hxc2000c02v1Entry 90 }

		-- 1.3.6.1.4.1.10106.3.101291.1.1.91
		hxc2000c02v1InIncFail OBJECT-TYPE
			SYNTAX BitFail
			MAX-ACCESS read-only
			STATUS current
			DESCRIPTION
				"Incompatible format fail"
		::= { hxc2000c02v1Entry 91 }

		-- 1.3.6.1.4.1.10106.3.101291.1.1.92
		hxc2000c02v1InIncFailTrapEnable OBJECT-TYPE
			SYNTAX AlarmEnable
			MAX-ACCESS read-write
			STATUS current
			DESCRIPTION
				"Incompatible format fail Trap Enable"
		::= { hxc2000c02v1Entry 92 }

		-- 1.3.6.1.4.1.10106.3.101291.1.1.93
		hxc2000c02v1InPresCrcFail OBJECT-TYPE
			SYNTAX BitFail
			MAX-ACCESS read-only
			STATUS current
			DESCRIPTION
				"EDH/CRC presence fail"
		::= { hxc2000c02v1Entry 93 }

		-- 1.3.6.1.4.1.10106.3.101291.1.1.95
		hxc2000c02v1InCrcFail OBJECT-TYPE
			SYNTAX BitFail
			MAX-ACCESS read-only
			STATUS current
			DESCRIPTION
				"EDH/CRC fail"
		::= { hxc2000c02v1Entry 95 }

		-- 1.3.6.1.4.1.10106.3.101291.1.1.96
		hxc2000c02v1InCrcFailTrapEnable OBJECT-TYPE
			SYNTAX AlarmEnable
			MAX-ACCESS read-write
			STATUS current
			DESCRIPTION
				"EDH/CRC fail Trap Enable"
		::= { hxc2000c02v1Entry 96 }

		-- 1.3.6.1.4.1.10106.3.101291.1.1.97
		hxc2000c02v1InPrsS352Fail OBJECT-TYPE
			SYNTAX BitFail
			MAX-ACCESS read-only
			STATUS current
			DESCRIPTION
				"SMPTE 352 presence fail"
		::= { hxc2000c02v1Entry 97 }

		-- 1.3.6.1.4.1.10106.3.101291.1.1.99
		hxc2000c02v1InS352Fail OBJECT-TYPE
			SYNTAX BitFail
			MAX-ACCESS read-only
			STATUS current
			DESCRIPTION
				"SMPTE 352 fail"
		::= { hxc2000c02v1Entry 99 }

		-- 1.3.6.1.4.1.10106.3.101291.1.1.101
		hxc2000c02v1PresS2016Fail OBJECT-TYPE
			SYNTAX BitFail
			MAX-ACCESS read-only
			STATUS current
			DESCRIPTION
				"SMPTE 2016 presence fail"
		::= { hxc2000c02v1Entry 101 }

		-- 1.3.6.1.4.1.10106.3.101291.1.1.103
		hxc2000c02v1ErrS2016Fail OBJECT-TYPE
			SYNTAX BitFail
			MAX-ACCESS read-only
			STATUS current
			DESCRIPTION
				"SMPTE 2016 error fail"
		::= { hxc2000c02v1Entry 103 }

		-- 1.3.6.1.4.1.10106.3.101291.1.1.105
		hxc2000c02v1PresAudG1Fail OBJECT-TYPE
			SYNTAX BitFail
			MAX-ACCESS read-only
			STATUS current
			DESCRIPTION
				"Audio group 1 presence fail"
		::= { hxc2000c02v1Entry 105 }

		-- 1.3.6.1.4.1.10106.3.101291.1.1.106
		hxc2000c02v1PresAudG1FailTrapEnable OBJECT-TYPE
			SYNTAX AlarmEnable
			MAX-ACCESS read-write
			STATUS current
			DESCRIPTION
				"Audio group 1 presence fail Trap Enable"
		::= { hxc2000c02v1Entry 106 }

		-- 1.3.6.1.4.1.10106.3.101291.1.1.107
		hxc2000c02v1PresAudG2Fail OBJECT-TYPE
			SYNTAX BitFail
			MAX-ACCESS read-only
			STATUS current
			DESCRIPTION
				"Audio group 2 presence fail"
		::= { hxc2000c02v1Entry 107 }

		-- 1.3.6.1.4.1.10106.3.101291.1.1.108
		hxc2000c02v1PresAudG2FailTrapEnable OBJECT-TYPE
			SYNTAX AlarmEnable
			MAX-ACCESS read-write
			STATUS current
			DESCRIPTION
				"Audio group 2 presence fail Trap Enable"
		::= { hxc2000c02v1Entry 108 }

		-- 1.3.6.1.4.1.10106.3.101291.1.1.109
		hxc2000c02v1PresAudG3Fail OBJECT-TYPE
			SYNTAX BitFail
			MAX-ACCESS read-only
			STATUS current
			DESCRIPTION
				"Audio group 3 presence fail"
		::= { hxc2000c02v1Entry 109 }

		-- 1.3.6.1.4.1.10106.3.101291.1.1.110
		hxc2000c02v1PresAudG3FailTrapEnable OBJECT-TYPE
			SYNTAX AlarmEnable
			MAX-ACCESS read-write
			STATUS current
			DESCRIPTION
				"Audio group 3 presence fail Trap Enable"
		::= { hxc2000c02v1Entry 110 }

		-- 1.3.6.1.4.1.10106.3.101291.1.1.111
		hxc2000c02v1PresAudG4Fail OBJECT-TYPE
			SYNTAX BitFail
			MAX-ACCESS read-only
			STATUS current
			DESCRIPTION
				"Audio group 4 presence fail"
		::= { hxc2000c02v1Entry 111 }

		-- 1.3.6.1.4.1.10106.3.101291.1.1.112
		hxc2000c02v1PresAudG4FailTrapEnable OBJECT-TYPE
			SYNTAX AlarmEnable
			MAX-ACCESS read-write
			STATUS current
			DESCRIPTION
				"Audio group 4 presence fail Trap Enable"
		::= { hxc2000c02v1Entry 112 }

		-- 1.3.6.1.4.1.10106.3.101291.1.1.113
		hxc2000c02v1RefFail OBJECT-TYPE
			SYNTAX BitFail
			MAX-ACCESS read-only
			STATUS current
			DESCRIPTION
				"Analog reference absence fail"
		::= { hxc2000c02v1Entry 113 }

		-- 1.3.6.1.4.1.10106.3.101291.1.1.114
		hxc2000c02v1RefFailTrapEnable OBJECT-TYPE
			SYNTAX AlarmEnable
			MAX-ACCESS read-write
			STATUS current
			DESCRIPTION
				"Analog reference absence fail Trap Enable"
		::= { hxc2000c02v1Entry 114 }

		-- 1.3.6.1.4.1.10106.3.101291.1.1.115
		hxc2000c02v1RefFmtFail OBJECT-TYPE
			SYNTAX BitFail
			MAX-ACCESS read-only
			STATUS current
			DESCRIPTION
				"Analog reference format fail"
		::= { hxc2000c02v1Entry 115 }

		-- 1.3.6.1.4.1.10106.3.101291.1.1.116
		hxc2000c02v1RefFmtFailTrapEnable OBJECT-TYPE
			SYNTAX AlarmEnable
			MAX-ACCESS read-write
			STATUS current
			DESCRIPTION
				"Analog reference format fail Trap Enable"
		::= { hxc2000c02v1Entry 116 }

		-- 1.3.6.1.4.1.10106.3.101291.1.1.117
		hxc2000c02v1LockFail OBJECT-TYPE
			SYNTAX BitFail
			MAX-ACCESS read-only
			STATUS current
			DESCRIPTION
				"Reference unlock fail"
		::= { hxc2000c02v1Entry 117 }

		-- 1.3.6.1.4.1.10106.3.101291.1.1.118
		hxc2000c02v1LockFailTrapEnable OBJECT-TYPE
			SYNTAX AlarmEnable
			MAX-ACCESS read-write
			STATUS current
			DESCRIPTION
				"Reference unlock fail Trap Enable"
		::= { hxc2000c02v1Entry 118 }

		-- 1.3.6.1.4.1.10106.3.101291.1.1.119
		hxc2000c02v1UxcPres OBJECT-TYPE
			SYNTAX BitFail
			MAX-ACCESS read-only
			STATUS current
			DESCRIPTION
				"UXC2000 presence"
		::= { hxc2000c02v1Entry 119 }

		-- 1.3.6.1.4.1.10106.3.101291.1.1.120
		hxc2000c02v1UxcPresTrapEnable OBJECT-TYPE
			SYNTAX AlarmEnable
			MAX-ACCESS read-write
			STATUS current
			DESCRIPTION
				"UXC2000 presence Trap Enable"
		::= { hxc2000c02v1Entry 120 }

		-- 1.3.6.1.4.1.10106.3.101291.1.1.121
		hxc2000c02v1AudPair0Fail OBJECT-TYPE
			SYNTAX BitFail
			MAX-ACCESS read-only
			STATUS current
			DESCRIPTION
				"Audio pair 0 fail"
		::= { hxc2000c02v1Entry 121 }

		-- 1.3.6.1.4.1.10106.3.101291.1.1.122
		hxc2000c02v1AudPair0FailTrapEnable OBJECT-TYPE
			SYNTAX AlarmEnable
			MAX-ACCESS read-write
			STATUS current
			DESCRIPTION
				"Audio pair 0 fail Trap Enable"
		::= { hxc2000c02v1Entry 122 }

		-- 1.3.6.1.4.1.10106.3.101291.1.1.123
		hxc2000c02v1AudPair1Fail OBJECT-TYPE
			SYNTAX BitFail
			MAX-ACCESS read-only
			STATUS current
			DESCRIPTION
				"Audio pair 1 fail"
		::= { hxc2000c02v1Entry 123 }

		-- 1.3.6.1.4.1.10106.3.101291.1.1.124
		hxc2000c02v1AudPair1FailTrapEnable OBJECT-TYPE
			SYNTAX AlarmEnable
			MAX-ACCESS read-write
			STATUS current
			DESCRIPTION
				"Audio pair 1 fail Trap Enable"
		::= { hxc2000c02v1Entry 124 }

		-- 1.3.6.1.4.1.10106.3.101291.1.1.125
		hxc2000c02v1AudPair2Fail OBJECT-TYPE
			SYNTAX BitFail
			MAX-ACCESS read-only
			STATUS current
			DESCRIPTION
				"Audio pair 2 fail"
		::= { hxc2000c02v1Entry 125 }

		-- 1.3.6.1.4.1.10106.3.101291.1.1.126
		hxc2000c02v1AudPair2FailTrapEnable OBJECT-TYPE
			SYNTAX AlarmEnable
			MAX-ACCESS read-write
			STATUS current
			DESCRIPTION
				"Audio pair 2 fail Trap Enable"
		::= { hxc2000c02v1Entry 126 }

		-- 1.3.6.1.4.1.10106.3.101291.1.1.127
		hxc2000c02v1AudPair3Fail OBJECT-TYPE
			SYNTAX BitFail
			MAX-ACCESS read-only
			STATUS current
			DESCRIPTION
				"Audio pair 3 fail"
		::= { hxc2000c02v1Entry 127 }

		-- 1.3.6.1.4.1.10106.3.101291.1.1.128
		hxc2000c02v1AudPair3FailTrapEnable OBJECT-TYPE
			SYNTAX AlarmEnable
			MAX-ACCESS read-write
			STATUS current
			DESCRIPTION
				"Audio pair 3 fail Trap Enable"
		::= { hxc2000c02v1Entry 128 }

		-- 1.3.6.1.4.1.10106.3.101291.1.1.129
		hxc2000c02v1AudPair4Fail OBJECT-TYPE
			SYNTAX BitFail
			MAX-ACCESS read-only
			STATUS current
			DESCRIPTION
				"Audio pair 4 fail"
		::= { hxc2000c02v1Entry 129 }

		-- 1.3.6.1.4.1.10106.3.101291.1.1.130
		hxc2000c02v1AudPair4FailTrapEnable OBJECT-TYPE
			SYNTAX AlarmEnable
			MAX-ACCESS read-write
			STATUS current
			DESCRIPTION
				"Audio pair 4 fail Trap Enable"
		::= { hxc2000c02v1Entry 130 }

		-- 1.3.6.1.4.1.10106.3.101291.1.1.131
		hxc2000c02v1AudPair5Fail OBJECT-TYPE
			SYNTAX BitFail
			MAX-ACCESS read-only
			STATUS current
			DESCRIPTION
				"Audio pair 5 fail"
		::= { hxc2000c02v1Entry 131 }

		-- 1.3.6.1.4.1.10106.3.101291.1.1.132
		hxc2000c02v1AudPair5FailTrapEnable OBJECT-TYPE
			SYNTAX AlarmEnable
			MAX-ACCESS read-write
			STATUS current
			DESCRIPTION
				"Audio pair 5 fail Trap Enable"
		::= { hxc2000c02v1Entry 132 }

		-- 1.3.6.1.4.1.10106.3.101291.1.1.133
		hxc2000c02v1AudPair6Fail OBJECT-TYPE
			SYNTAX BitFail
			MAX-ACCESS read-only
			STATUS current
			DESCRIPTION
				"Audio pair 6 fail"
		::= { hxc2000c02v1Entry 133 }

		-- 1.3.6.1.4.1.10106.3.101291.1.1.134
		hxc2000c02v1AudPair6FailTrapEnable OBJECT-TYPE
			SYNTAX AlarmEnable
			MAX-ACCESS read-write
			STATUS current
			DESCRIPTION
				"Audio pair 6 fail Trap Enable"
		::= { hxc2000c02v1Entry 134 }

		-- 1.3.6.1.4.1.10106.3.101291.1.1.135
		hxc2000c02v1AudPair7Fail OBJECT-TYPE
			SYNTAX BitFail
			MAX-ACCESS read-only
			STATUS current
			DESCRIPTION
				"Audio pair 7 fail"
		::= { hxc2000c02v1Entry 135 }

		-- 1.3.6.1.4.1.10106.3.101291.1.1.136
		hxc2000c02v1AudPair7FailTrapEnable OBJECT-TYPE
			SYNTAX AlarmEnable
			MAX-ACCESS read-write
			STATUS current
			DESCRIPTION
				"Audio pair 7 fail Trap Enable"
		::= { hxc2000c02v1Entry 136 }

		-- 1.3.6.1.4.1.10106.3.101291.1.1.137
		hxc2000c02v1InAfdDetct OBJECT-TYPE
			SYNTAX Afd1
			MAX-ACCESS read-only
			STATUS current
			DESCRIPTION
				"Input detected AFD"
		::= { hxc2000c02v1Entry 137 }

		-- 1.3.6.1.4.1.10106.3.101291.1.1.138
		hxc2000c02v1InAfdDetctTrapEnable OBJECT-TYPE
			SYNTAX AlarmEnable
			MAX-ACCESS read-write
			STATUS current
			DESCRIPTION
				"Input detected AFD Trap Enable"
		::= { hxc2000c02v1Entry 138 }

		-- 1.3.6.1.4.1.10106.3.101291.1.1.139
		hxc2000c02v1InCfDetct OBJECT-TYPE
			SYNTAX Cf1
			MAX-ACCESS read-only
			STATUS current
			DESCRIPTION
				"Input detected coded frame"
		::= { hxc2000c02v1Entry 139 }

		-- 1.3.6.1.4.1.10106.3.101291.1.1.140
		hxc2000c02v1InCfDetctTrapEnable OBJECT-TYPE
			SYNTAX AlarmEnable
			MAX-ACCESS read-write
			STATUS current
			DESCRIPTION
				"Input detected coded frame Trap Enable"
		::= { hxc2000c02v1Entry 140 }

		-- 1.3.6.1.4.1.10106.3.101291.1.1.141
		hxc2000c02v1InFormat OBJECT-TYPE
			SYNTAX SdiHd12gFmt3
			MAX-ACCESS read-only
			STATUS current
			DESCRIPTION
				"Input format"
		::= { hxc2000c02v1Entry 141 }

		-- 1.3.6.1.4.1.10106.3.101291.1.1.142
		hxc2000c02v1InFormatTrapEnable OBJECT-TYPE
			SYNTAX AlarmEnable
			MAX-ACCESS read-write
			STATUS current
			DESCRIPTION
				"Input format Trap Enable"
		::= { hxc2000c02v1Entry 142 }

		-- 1.3.6.1.4.1.10106.3.101291.1.1.143
		hxc2000c02v1RefFormat OBJECT-TYPE
			SYNTAX SdiHd12gFmt3
			MAX-ACCESS read-only
			STATUS current
			DESCRIPTION
				"Reference format"
		::= { hxc2000c02v1Entry 143 }

		-- 1.3.6.1.4.1.10106.3.101291.1.1.144
		hxc2000c02v1RefFormatTrapEnable OBJECT-TYPE
			SYNTAX AlarmEnable
			MAX-ACCESS read-write
			STATUS current
			DESCRIPTION
				"Reference format Trap Enable"
		::= { hxc2000c02v1Entry 144 }

		-- 1.3.6.1.4.1.10106.3.101291.1.1.145
		hxc2000c02v1TxFormat OBJECT-TYPE
			SYNTAX SdiHd3gFmt3
			MAX-ACCESS read-only
			STATUS current
			DESCRIPTION
				"Output format"
		::= { hxc2000c02v1Entry 145 }

		-- 1.3.6.1.4.1.10106.3.101291.1.1.146
		hxc2000c02v1TxFormatTrapEnable OBJECT-TYPE
			SYNTAX AlarmEnable
			MAX-ACCESS read-write
			STATUS current
			DESCRIPTION
				"Output format Trap Enable"
		::= { hxc2000c02v1Entry 146 }

		-- 1.3.6.1.4.1.10106.3.101291.1.1.147
		hxc2000c02v1TxtPres OBJECT-TYPE
			SYNTAX BitFailN
			MAX-ACCESS read-only
			STATUS current
			DESCRIPTION
				"TXT presence"
		::= { hxc2000c02v1Entry 147 }

		-- 1.3.6.1.4.1.10106.3.101291.1.1.149
		hxc2000c02v1VitcPres OBJECT-TYPE
			SYNTAX BitFailN
			MAX-ACCESS read-only
			STATUS current
			DESCRIPTION
				"VITC presence"
		::= { hxc2000c02v1Entry 149 }

		-- 1.3.6.1.4.1.10106.3.101291.1.1.151
		hxc2000c02v1Mute OBJECT-TYPE
			SYNTAX Bit0No1Yes
			MAX-ACCESS read-only
			STATUS current
			DESCRIPTION
				"Muted output"
		::= { hxc2000c02v1Entry 151 }

		-- 1.3.6.1.4.1.10106.3.101291.1.1.153
		hxc2000c02v1Black OBJECT-TYPE
			SYNTAX Bit0No1Yes
			MAX-ACCESS read-only
			STATUS current
			DESCRIPTION
				"Black output"
		::= { hxc2000c02v1Entry 153 }

		-- 1.3.6.1.4.1.10106.3.101291.1.1.155
		hxc2000c02v1Gpi1 OBJECT-TYPE
			SYNTAX Bit0Off1On
			MAX-ACCESS read-only
			STATUS current
			DESCRIPTION
				"Transmitted GPI1"
		::= { hxc2000c02v1Entry 155 }

		-- 1.3.6.1.4.1.10106.3.101291.1.1.157
		hxc2000c02v1Gpi2 OBJECT-TYPE
			SYNTAX Bit0Off1On
			MAX-ACCESS read-only
			STATUS current
			DESCRIPTION
				"Transmitted GPI2"
		::= { hxc2000c02v1Entry 157 }

		-- 1.3.6.1.4.1.10106.3.101291.1.1.159
		hxc2000c02v1Gpi3 OBJECT-TYPE
			SYNTAX Bit0Off1On
			MAX-ACCESS read-only
			STATUS current
			DESCRIPTION
				"Transmitted GPI3"
		::= { hxc2000c02v1Entry 159 }

		-- 1.3.6.1.4.1.10106.3.101291.1.1.161
		hxc2000c02v1Gpi4 OBJECT-TYPE
			SYNTAX Bit0Off1On
			MAX-ACCESS read-only
			STATUS current
			DESCRIPTION
				"Transmitted GPI4"
		::= { hxc2000c02v1Entry 161 }

		-- 1.3.6.1.4.1.10106.3.101291.1.1.163
		hxc2000c02v1SerialNo OBJECT-TYPE
			SYNTAX SerialNo
			MAX-ACCESS read-only
			STATUS current
			DESCRIPTION
				"Serial number"
		::= { hxc2000c02v1Entry 163 }

		-- 1.3.6.1.4.1.10106.3.623301
		mpx2000c01v1 OBJECT IDENTIFIER ::= { albalaProducts 623301 }

		-- 1.3.6.1.4.1.10106.3.623301.1
		mpx2000c01v1Table  OBJECT-TYPE
			SYNTAX SEQUENCE OF Mpx2000c01v1Entry
			MAX-ACCESS not-accessible
			STATUS current
			DESCRIPTION
				"Module  MPX2000C01V1 Table"
			::= { mpx2000c01v1 1 }

		-- 1.3.6.1.4.1.10106.3.623301.1.1
		mpx2000c01v1Entry  OBJECT-TYPE
			SYNTAX Mpx2000c01v1Entry
			MAX-ACCESS not-accessible
			STATUS current
			DESCRIPTION
				"Module MPX2000C01V1 Entry"
			INDEX { mpx2000c01v1Index }
			::= { mpx2000c01v1Table 1 }

			Mpx2000c01v1Entry ::=
			SEQUENCE {
				mpx2000c01v1Index
				ModuleIndex,
				mpx2000c01v1AudioMpxN
				BitMask,
				mpx2000c01v1AudioMpxNTrapEnable
				AlarmEnable,
				mpx2000c01v1Control
				MpxControl,
				mpx2000c01v1ControlTrapEnable
				AlarmEnable,
				mpx2000c01v1Preemph
				MpxPreemp,
				mpx2000c01v1AudInLevAdj
				MpxGain1,
				mpx2000c01v1NoSigThr
				MpxLevV,
				mpx2000c01v1NoSigTout
				TimeS1,
				mpx2000c01v1MpxFail
				BitFail,
				mpx2000c01v1MpxFailTrapEnable
				AlarmEnable,
				mpx2000c01v1AudFail
				BitFail,
				mpx2000c01v1AudFailTrapEnable
				AlarmEnable,
				mpx2000c01v1Gpi
				Bit0Open1Clo,
				mpx2000c01v1GpiTrapEnable
				AlarmEnable,
				mpx2000c01v1Gpo
				Bit0Open1Clo,
				mpx2000c01v1MpxPeakV
				MpxLevV,
				mpx2000c01v1InsPeakV
				MpxLevV,
				mpx2000c01v1MpxPeakDbfs
				MpxLevDbu,
				mpx2000c01v1AudPeakDbfs
				MpxLevDbu,
				mpx2000c01v1SerialNo
				SerialNo
			 }

		-- 1.3.6.1.4.1.10106.3.101291.1.1.1
		mpx2000c01v1Index OBJECT-TYPE
			SYNTAX ModuleIndex
			MAX-ACCESS read-only
			STATUS current
			DESCRIPTION
				"Index of MPX2000C01V1 Table"
		::= { mpx2000c01v1Entry 1 }

		-- 1.3.6.1.4.1.10106.3.101291.1.1.3
		mpx2000c01v1AudioMpxN OBJECT-TYPE
			SYNTAX BitMask
			MAX-ACCESS read-write
			STATUS current
			DESCRIPTION
				"Inserts audio"
		::= { mpx2000c01v1Entry 3 }

		-- 1.3.6.1.4.1.10106.3.101291.1.1.4
		mpx2000c01v1AudioMpxNTrapEnable OBJECT-TYPE
			SYNTAX AlarmEnable
			MAX-ACCESS read-write
			STATUS current
			DESCRIPTION
				"Inserts audio Trap Enable"
		::= { mpx2000c01v1Entry 4 }

		-- 1.3.6.1.4.1.10106.3.101291.1.1.5
		mpx2000c01v1Control OBJECT-TYPE
			SYNTAX MpxControl
			MAX-ACCESS read-write
			STATUS current
			DESCRIPTION
				"Control mode"
		::= { mpx2000c01v1Entry 5 }

		-- 1.3.6.1.4.1.10106.3.101291.1.1.6
		mpx2000c01v1ControlTrapEnable OBJECT-TYPE
			SYNTAX AlarmEnable
			MAX-ACCESS read-write
			STATUS current
			DESCRIPTION
				"Control mode Trap Enable"
		::= { mpx2000c01v1Entry 6 }

		-- 1.3.6.1.4.1.10106.3.101291.1.1.7
		mpx2000c01v1Preemph OBJECT-TYPE
			SYNTAX MpxPreemp
			MAX-ACCESS read-write
			STATUS current
			DESCRIPTION
				"Preemphasis"
		::= { mpx2000c01v1Entry 7 }

		-- 1.3.6.1.4.1.10106.3.101291.1.1.9
		mpx2000c01v1AudInLevAdj OBJECT-TYPE
			SYNTAX MpxGain1
			MAX-ACCESS read-write
			STATUS current
			DESCRIPTION
				"AUD level adjust"
		::= { mpx2000c01v1Entry 9 }

		-- 1.3.6.1.4.1.10106.3.101291.1.1.11
		mpx2000c01v1NoSigThr OBJECT-TYPE
			SYNTAX MpxLevV
			MAX-ACCESS read-write
			STATUS current
			DESCRIPTION
				"Signal absence threshold"
		::= { mpx2000c01v1Entry 11 }

		-- 1.3.6.1.4.1.10106.3.101291.1.1.13
		mpx2000c01v1NoSigTout OBJECT-TYPE
			SYNTAX TimeS1
			MAX-ACCESS read-write
			STATUS current
			DESCRIPTION
				"Signal abssence timeout"
		::= { mpx2000c01v1Entry 13 }

		-- 1.3.6.1.4.1.10106.3.101291.1.1.15
		mpx2000c01v1MpxFail OBJECT-TYPE
			SYNTAX BitFail
			MAX-ACCESS read-only
			STATUS current
			DESCRIPTION
				"MPX signal absence"
		::= { mpx2000c01v1Entry 15 }

		-- 1.3.6.1.4.1.10106.3.101291.1.1.16
		mpx2000c01v1MpxFailTrapEnable OBJECT-TYPE
			SYNTAX AlarmEnable
			MAX-ACCESS read-write
			STATUS current
			DESCRIPTION
				"MPX signal absence Trap Enable"
		::= { mpx2000c01v1Entry 16 }

		-- 1.3.6.1.4.1.10106.3.101291.1.1.17
		mpx2000c01v1AudFail OBJECT-TYPE
			SYNTAX BitFail
			MAX-ACCESS read-only
			STATUS current
			DESCRIPTION
				"AUD signal absence"
		::= { mpx2000c01v1Entry 17 }

		-- 1.3.6.1.4.1.10106.3.101291.1.1.18
		mpx2000c01v1AudFailTrapEnable OBJECT-TYPE
			SYNTAX AlarmEnable
			MAX-ACCESS read-write
			STATUS current
			DESCRIPTION
				"AUD signal absence Trap Enable"
		::= { mpx2000c01v1Entry 18 }

		-- 1.3.6.1.4.1.10106.3.101291.1.1.19
		mpx2000c01v1Gpi OBJECT-TYPE
			SYNTAX Bit0Open1Clo
			MAX-ACCESS read-only
			STATUS current
			DESCRIPTION
				"GPI"
		::= { mpx2000c01v1Entry 19 }

		-- 1.3.6.1.4.1.10106.3.101291.1.1.20
		mpx2000c01v1GpiTrapEnable OBJECT-TYPE
			SYNTAX AlarmEnable
			MAX-ACCESS read-write
			STATUS current
			DESCRIPTION
				"GPI Trap Enable"
		::= { mpx2000c01v1Entry 20 }

		-- 1.3.6.1.4.1.10106.3.101291.1.1.21
		mpx2000c01v1Gpo OBJECT-TYPE
			SYNTAX Bit0Open1Clo
			MAX-ACCESS read-only
			STATUS current
			DESCRIPTION
				"GPO"
		::= { mpx2000c01v1Entry 21 }

		-- 1.3.6.1.4.1.10106.3.101291.1.1.23
		mpx2000c01v1MpxPeakV OBJECT-TYPE
			SYNTAX MpxLevV
			MAX-ACCESS read-only
			STATUS current
			DESCRIPTION
				"MPX peak level"
		::= { mpx2000c01v1Entry 23 }

		-- 1.3.6.1.4.1.10106.3.101291.1.1.25
		mpx2000c01v1InsPeakV OBJECT-TYPE
			SYNTAX MpxLevV
			MAX-ACCESS read-only
			STATUS current
			DESCRIPTION
				"AUD peak  level"
		::= { mpx2000c01v1Entry 25 }

		-- 1.3.6.1.4.1.10106.3.101291.1.1.27
		mpx2000c01v1MpxPeakDbfs OBJECT-TYPE
			SYNTAX MpxLevDbu
			MAX-ACCESS read-only
			STATUS current
			DESCRIPTION
				"MPX peak level"
		::= { mpx2000c01v1Entry 27 }

		-- 1.3.6.1.4.1.10106.3.101291.1.1.29
		mpx2000c01v1AudPeakDbfs OBJECT-TYPE
			SYNTAX MpxLevDbu
			MAX-ACCESS read-only
			STATUS current
			DESCRIPTION
				"AUD peak  level"
		::= { mpx2000c01v1Entry 29 }

		-- 1.3.6.1.4.1.10106.3.101291.1.1.31
		mpx2000c01v1SerialNo OBJECT-TYPE
			SYNTAX SerialNo
			MAX-ACCESS read-only
			STATUS current
			DESCRIPTION
				"Serial number"
		::= { mpx2000c01v1Entry 31 }

		-- 1.3.6.1.4.1.10106.3.627101
		rfa2018c01v1 OBJECT IDENTIFIER ::= { albalaProducts 627101 }

		-- 1.3.6.1.4.1.10106.3.627101.1
		rfa2018c01v1Table  OBJECT-TYPE
			SYNTAX SEQUENCE OF Rfa2018c01v1Entry
			MAX-ACCESS not-accessible
			STATUS current
			DESCRIPTION
				"Module  RFA2018C01V1 Table"
			::= { rfa2018c01v1 1 }

		-- 1.3.6.1.4.1.10106.3.627101.1.1
		rfa2018c01v1Entry  OBJECT-TYPE
			SYNTAX Rfa2018c01v1Entry
			MAX-ACCESS not-accessible
			STATUS current
			DESCRIPTION
				"Module RFA2018C01V1 Entry"
			INDEX { rfa2018c01v1Index }
			::= { rfa2018c01v1Table 1 }

			Rfa2018c01v1Entry ::=
			SEQUENCE {
				rfa2018c01v1Index
				ModuleIndex,
				rfa2018c01v1VoltFailMask
				BitMask,
				rfa2018c01v1CurrFailMask
				BitMask,
				rfa2018c01v1TempFailMask
				BitMask,
				rfa2018c01v1MinVoltThr
				RfaVoltage,
				rfa2018c01v1MaxVoltThr
				RfaVoltage,
				rfa2018c01v1MinCurrThr
				RfaCurrent,
				rfa2018c01v1MaxCurrThr
				RfaCurrent,
				rfa2018c01v1MaxTempThr
				Temperature0c1,
				rfa2018c01v1VoltFail
				BitFail,
				rfa2018c01v1VoltFailTrapEnable
				AlarmEnable,
				rfa2018c01v1CurrFail
				BitFail,
				rfa2018c01v1CurrFailTrapEnable
				AlarmEnable,
				rfa2018c01v1TempFail
				BitFail,
				rfa2018c01v1TempFailTrapEnable
				AlarmEnable,
				rfa2018c01v1ActVolt
				RfaVoltage,
				rfa2018c01v1ActCurr
				RfaCurrent,
				rfa2018c01v1ActTemp
				Temperature0c1,
				rfa2018c01v1SerialNo
				SerialNo
			 }

		-- 1.3.6.1.4.1.10106.3.101291.1.1.1
		rfa2018c01v1Index OBJECT-TYPE
			SYNTAX ModuleIndex
			MAX-ACCESS read-only
			STATUS current
			DESCRIPTION
				"Index of RFA2018C01V1 Table"
		::= { rfa2018c01v1Entry 1 }

		-- 1.3.6.1.4.1.10106.3.101291.1.1.3
		rfa2018c01v1VoltFailMask OBJECT-TYPE
			SYNTAX BitMask
			MAX-ACCESS read-write
			STATUS current
			DESCRIPTION
				"Allows masking voltage fail"
		::= { rfa2018c01v1Entry 3 }

		-- 1.3.6.1.4.1.10106.3.101291.1.1.5
		rfa2018c01v1CurrFailMask OBJECT-TYPE
			SYNTAX BitMask
			MAX-ACCESS read-write
			STATUS current
			DESCRIPTION
				"Allows masking current fail"
		::= { rfa2018c01v1Entry 5 }

		-- 1.3.6.1.4.1.10106.3.101291.1.1.7
		rfa2018c01v1TempFailMask OBJECT-TYPE
			SYNTAX BitMask
			MAX-ACCESS read-write
			STATUS current
			DESCRIPTION
				"Allows masking temperature fail"
		::= { rfa2018c01v1Entry 7 }

		-- 1.3.6.1.4.1.10106.3.101291.1.1.9
		rfa2018c01v1MinVoltThr OBJECT-TYPE
			SYNTAX RfaVoltage
			MAX-ACCESS read-write
			STATUS current
			DESCRIPTION
				"Allows adjusting minimum voltage threshold"
		::= { rfa2018c01v1Entry 9 }

		-- 1.3.6.1.4.1.10106.3.101291.1.1.11
		rfa2018c01v1MaxVoltThr OBJECT-TYPE
			SYNTAX RfaVoltage
			MAX-ACCESS read-write
			STATUS current
			DESCRIPTION
				"Allows adjusting maximum voltage threshold"
		::= { rfa2018c01v1Entry 11 }

		-- 1.3.6.1.4.1.10106.3.101291.1.1.13
		rfa2018c01v1MinCurrThr OBJECT-TYPE
			SYNTAX RfaCurrent
			MAX-ACCESS read-write
			STATUS current
			DESCRIPTION
				"Allows adjusting minimum current threshold"
		::= { rfa2018c01v1Entry 13 }

		-- 1.3.6.1.4.1.10106.3.101291.1.1.15
		rfa2018c01v1MaxCurrThr OBJECT-TYPE
			SYNTAX RfaCurrent
			MAX-ACCESS read-write
			STATUS current
			DESCRIPTION
				"Allows adjusting maximum current threshold"
		::= { rfa2018c01v1Entry 15 }

		-- 1.3.6.1.4.1.10106.3.101291.1.1.17
		rfa2018c01v1MaxTempThr OBJECT-TYPE
			SYNTAX Temperature0c1
			MAX-ACCESS read-write
			STATUS current
			DESCRIPTION
				"Allows adjusting maximum temperature threshold"
		::= { rfa2018c01v1Entry 17 }

		-- 1.3.6.1.4.1.10106.3.101291.1.1.19
		rfa2018c01v1VoltFail OBJECT-TYPE
			SYNTAX BitFail
			MAX-ACCESS read-only
			STATUS current
			DESCRIPTION
				"Indicates that actual votage is out of recommended range"
		::= { rfa2018c01v1Entry 19 }

		-- 1.3.6.1.4.1.10106.3.101291.1.1.20
		rfa2018c01v1VoltFailTrapEnable OBJECT-TYPE
			SYNTAX AlarmEnable
			MAX-ACCESS read-write
			STATUS current
			DESCRIPTION
				"Indicates that actual votage is out of recommended range Trap Enable"
		::= { rfa2018c01v1Entry 20 }

		-- 1.3.6.1.4.1.10106.3.101291.1.1.21
		rfa2018c01v1CurrFail OBJECT-TYPE
			SYNTAX BitFail
			MAX-ACCESS read-only
			STATUS current
			DESCRIPTION
				"Indicates that actual current is out of recommended range"
		::= { rfa2018c01v1Entry 21 }

		-- 1.3.6.1.4.1.10106.3.101291.1.1.22
		rfa2018c01v1CurrFailTrapEnable OBJECT-TYPE
			SYNTAX AlarmEnable
			MAX-ACCESS read-write
			STATUS current
			DESCRIPTION
				"Indicates that actual current is out of recommended range Trap Enable"
		::= { rfa2018c01v1Entry 22 }

		-- 1.3.6.1.4.1.10106.3.101291.1.1.23
		rfa2018c01v1TempFail OBJECT-TYPE
			SYNTAX BitFail
			MAX-ACCESS read-only
			STATUS current
			DESCRIPTION
				"Indicates that actual temperature is over recommended range"
		::= { rfa2018c01v1Entry 23 }

		-- 1.3.6.1.4.1.10106.3.101291.1.1.24
		rfa2018c01v1TempFailTrapEnable OBJECT-TYPE
			SYNTAX AlarmEnable
			MAX-ACCESS read-write
			STATUS current
			DESCRIPTION
				"Indicates that actual temperature is over recommended range Trap Enable"
		::= { rfa2018c01v1Entry 24 }

		-- 1.3.6.1.4.1.10106.3.101291.1.1.25
		rfa2018c01v1ActVolt OBJECT-TYPE
			SYNTAX RfaVoltage
			MAX-ACCESS read-only
			STATUS current
			DESCRIPTION
				"Displays the DC output voltaje"
		::= { rfa2018c01v1Entry 25 }

		-- 1.3.6.1.4.1.10106.3.101291.1.1.27
		rfa2018c01v1ActCurr OBJECT-TYPE
			SYNTAX RfaCurrent
			MAX-ACCESS read-only
			STATUS current
			DESCRIPTION
				"Displays the DC output current"
		::= { rfa2018c01v1Entry 27 }

		-- 1.3.6.1.4.1.10106.3.101291.1.1.29
		rfa2018c01v1ActTemp OBJECT-TYPE
			SYNTAX Temperature0c1
			MAX-ACCESS read-only
			STATUS current
			DESCRIPTION
				"Displays temperature"
		::= { rfa2018c01v1Entry 29 }

		-- 1.3.6.1.4.1.10106.3.101291.1.1.31
		rfa2018c01v1SerialNo OBJECT-TYPE
			SYNTAX SerialNo
			MAX-ACCESS read-only
			STATUS current
			DESCRIPTION
				"Serial number"
		::= { rfa2018c01v1Entry 31 }
		
		
	
	END

--
-- ALBALA-MIB.my
--
