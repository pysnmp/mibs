--
-- IRT-FM-NPLUS1-MIB.my
-- MIB generated by MG-SOFT Visual MIB Builder Version 6.0  Build 88
-- Wednesday, May 23, 2007 at 19:44:14
--

	IRT-FM-NPLUS1-MIB DEFINITIONS ::= BEGIN
 
		IMPORTS
			eventTimeStamp, eventPriority, eventCounter, mibRelease			
				FROM IRT-COMMONVARBINDS-MIB			
			fm, LocalRemote, FaultOK, SelectManualAuto, ReadyNotReady, 
			ExecutedNotExecuted, SelectOnOff, PresentNotPresent, WarningOK			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			TruthValue, TEXTUAL-CONVENTION			
				FROM SNMPv2-TC;
	
	
		-- 1.3.6.1.4.1.19831.1.1.3.5
		fmnPlus1 MODULE-IDENTITY 
			LAST-UPDATED "200705041400Z"		-- May 04, 2007 at 14:00 GMT
			ORGANIZATION 
				"IRT for WORKING-GROUP-TC-MIB"
			CONTACT-INFO 
				"Contact-info:
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				
				branch definition
				
				1st level
				
				events                         OBJECT IDENTIFIER ::= { dvbnPlus1 0 }
				dvbnPlus1General               OBJECT IDENTIFIER ::= { dvbnPlus1 1 }
				  dvbnPlus1MainTransmitterTable   is defined below as dvbnPlus1 2
				dvbnPlus1ReserveTransmitter    OBJECT IDENTIFIER ::= { dvbnPlus1 3 }
				  dvbnPlus1TransmitterATable      is defined below as dvbnPlus1 4
				dvbnPlus1TransmitterB          OBJECT IDENTIFIER ::= { dvbnPlus1 5 }
				dvbnPlus1EventEnable           OBJECT IDENTIFIER ::= { dvbnPlus1 6 }
				dvbnPlus1EventPriority         OBJECT IDENTIFIER ::= { dvbnPlus1 7 }
				groups                         OBJECT IDENTIFIER ::= { dvbnPlus1 8 }
				
				
				2nd level
				
				dvbnPlus1EventEnableGeneral                OBJECT IDENTIFIER ::= { dvbnPlus1EventEnable 1 }
				  dvbnPlus1EventEnableMainTransmitterTable    is defined below as dvbnPlus1EventEnable 2
				dvbnPlus1EventEnableReserveTransmitter     OBJECT IDENTIFIER ::= { dvbnPlus1EventEnable 3 }
				  dvbnPlus1EventEnableTransmitterATable       is defined below as dvbnPlus1EventEnable 4 }
				dvbnPlus1EventEnableTransmitterB           OBJECT IDENTIFIER ::= { dvbnPlus1EventEnable 5 }
				
				dvbnPlus1EventPriorityGeneral              OBJECT IDENTIFIER ::= { dvbnPlus1EventPriority 1 }
				  dvbnPlus1EventPriorityMainTransmitterTable  is defined below as dvbnPlus1EventPriority 2
				dvbnPlus1EventPriorityReserveTransmitter   OBJECT IDENTIFIER ::= { dvbnPlus1EventPriority 3 }
				  dvbnPlus1EventPriorityTransmitterATable     is defined below as dvbnPlus1EventPriority 4
				dvbnPlus1EventPriorityTransmitterB         OBJECT IDENTIFIER ::= { dvbnPlus1EventPriority 5 }
				
				end branch"
			REVISION "200705041400Z"		-- May 04, 2007 at 14:00 GMT
			DESCRIPTION 
				"change LocalMode (description) and Module-COMPLIANCE
				change MAX-ACCESS: OIDs 1.3.6.1.4.1.19831.1.1.3.5.6.5.1 and
				1.3.6.1.4.1.19831.1.1.3.5.6.5.3
				change numbering: OIDs
				1.3.6.1.4.1.19831.1.1.3.5.3.x and
				1.3.6.1.4.1.19831.1.1.3.5.5.x and
				1.3.6.1.4.1.19831.1.1.3.5.6.2.1.x and
				1.3.6.1.4.1.19831.1.1.3.5.6.3.x and
				1.3.6.1.4.1.19831.1.1.3.5.6.4.1.x and
				1.3.6.1.4.1.19831.1.1.3.5.6.5.x and
				1.3.6.1.4.1.19831.1.1.3.5.7.2.1.x and
				1.3.6.1.4.1.19831.1.1.3.5.7.3.x and
				1.3.6.1.4.1.19831.1.1.3.5.7.4.1.x and
				1.3.6.1.4.1.19831.1.1.3.5.7.5.x"
			REVISION "200612201400Z"		-- December 20, 2006 at 14:00 GMT
			DESCRIPTION 
				"Corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { fm 5 }

		
	
--
-- Textual conventions
--
	
		TransmitterBFreeOccupied ::= TEXTUAL-CONVENTION
			STATUS obsolete
			DESCRIPTION 
				"Description. Free/Occupied message for transmitter B
				
				(1) free              
				(2) occupied          "
			SYNTAX INTEGER
				{
				free(1),
				occupied(2)
				}

	
--
-- Node definitions
--
	
-- fm N+1 Reserve. Events
		-- 1.3.6.1.4.1.19831.1.1.3.5.0
		fmEventsnPlus1 OBJECT IDENTIFIER ::= { fmnPlus1 0 }

		
		-- 1.3.6.1.4.1.19831.1.1.3.5.0.1
		fmnPlus1RedundancySwitchOverEvent NOTIFICATION-TYPE
			OBJECTS { sysDescr, sysName, sysLocation, eventTimeStamp, eventPriority, 
				eventCounter, fmnPlus1RedundancySwitchOver }
			STATUS current
			DESCRIPTION 
				"Description. fmnPlus1RedundancySwitchOver notification"
			::= { fmEventsnPlus1 1 }

		
		-- 1.3.6.1.4.1.19831.1.1.3.5.0.2
		fmnPlus1LocalModeEvent NOTIFICATION-TYPE
			OBJECTS { sysDescr, sysName, sysLocation, eventTimeStamp, eventPriority, 
				eventCounter, fmnPlus1LocalMode }
			STATUS current
			DESCRIPTION 
				"Description.fmnPlus1LocalMode notification"
			::= { fmEventsnPlus1 2 }

		
		-- 1.3.6.1.4.1.19831.1.1.3.5.0.3
		fmnPlus1ControlUnitFaultEvent NOTIFICATION-TYPE
			OBJECTS { sysDescr, sysName, sysLocation, eventTimeStamp, eventPriority, 
				eventCounter, fmnPlus1ControlUnitFault }
			STATUS current
			DESCRIPTION 
				"Description. fmnPlus1ControlUnitFault notification"
			::= { fmEventsnPlus1 3 }

		
		-- 1.3.6.1.4.1.19831.1.1.3.5.0.4
		fmnPlus1SwitchOverModeEvent NOTIFICATION-TYPE
			OBJECTS { sysDescr, sysName, sysLocation, eventTimeStamp, eventPriority, 
				eventCounter, fmnPlus1SwitchOverMode }
			STATUS current
			DESCRIPTION 
				"Description. fmnPlus1SwitchOverMode notification"
			::= { fmEventsnPlus1 4 }

		
		-- 1.3.6.1.4.1.19831.1.1.3.5.0.5
		fmnPlus1SwitchOverReadyEvent NOTIFICATION-TYPE
			OBJECTS { sysDescr, sysName, sysLocation, eventTimeStamp, eventPriority, 
				eventCounter, fmnPlus1SwitchOverReady }
			STATUS current
			DESCRIPTION 
				"Description. fmnPlus1SwitchOverReady notification"
			::= { fmEventsnPlus1 5 }

		
		-- 1.3.6.1.4.1.19831.1.1.3.5.0.6
		fmnPlus1SwitchOverExecutedEvent NOTIFICATION-TYPE
			OBJECTS { sysDescr, sysName, sysLocation, eventTimeStamp, eventPriority, 
				eventCounter, fmnPlus1SwitchOverExecuted }
			STATUS current
			DESCRIPTION 
				"Description. fmnPlus1SwitchOverExecuted notification"
			::= { fmEventsnPlus1 6 }

		
		-- 1.3.6.1.4.1.19831.1.1.3.5.0.7
		fmnPlus1SwitchOverFaultEvent NOTIFICATION-TYPE
			OBJECTS { sysDescr, sysName, sysLocation, eventTimeStamp, eventPriority, 
				eventCounter, fmnPlus1SwitchOverFault }
			STATUS current
			DESCRIPTION 
				"Description. fmnPlus1SwitchOverFault notification"
			::= { fmEventsnPlus1 7 }

		
		-- 1.3.6.1.4.1.19831.1.1.3.5.0.8
		fmnPlus1ChannelSelectionEvent NOTIFICATION-TYPE
			OBJECTS { sysDescr, sysName, sysLocation, eventTimeStamp, eventPriority, 
				eventCounter, fmnPlus1ChannelSelection }
			STATUS current
			DESCRIPTION 
				"Description. fmnPlus1ChannelSelection notification"
			::= { fmEventsnPlus1 8 }

		
		-- 1.3.6.1.4.1.19831.1.1.3.5.0.9
		fmnPlus1TransmitterBResetEvent NOTIFICATION-TYPE
			OBJECTS { sysDescr, sysName, sysLocation, eventTimeStamp, eventPriority, 
				eventCounter, fmnPlus1TransmitterBReset }
			STATUS obsolete
			DESCRIPTION 
				"Notification is not active!
				
				Description. fmnPlus1TransmitterBReset notification"
			::= { fmEventsnPlus1 9 }

		
		-- 1.3.6.1.4.1.19831.1.1.3.5.0.10
		fmnPlus1TransmitterBModeEvent NOTIFICATION-TYPE
			OBJECTS { sysDescr, sysName, sysLocation, eventTimeStamp, eventPriority, 
				eventCounter, fmnPlus1TransmitterBMode }
			STATUS obsolete
			DESCRIPTION 
				"Notification is not avtive!
				
				Description. fmnPlus1TransmitterBMode notification"
			::= { fmEventsnPlus1 10 }

		
		-- 1.3.6.1.4.1.19831.1.1.3.5.0.11
		fmnPlus1MTOpModeEvent NOTIFICATION-TYPE
			OBJECTS { sysDescr, sysName, sysLocation, eventTimeStamp, eventPriority, 
				eventCounter, fmnPlus1MTOpMode, fmnPlus1EventTransmitterIndex }
			STATUS current
			DESCRIPTION 
				"Description. fmnPlus1MTOpMode notification"
			::= { fmEventsnPlus1 11 }

		
		-- 1.3.6.1.4.1.19831.1.1.3.5.0.12
		fmnPlus1MTRFProgramPresentEvent NOTIFICATION-TYPE
			OBJECTS { sysDescr, sysName, sysLocation, eventTimeStamp, eventPriority, 
				eventCounter, fmnPlus1MTRFProgramPresent, fmnPlus1EventTransmitterIndex }
			STATUS current
			DESCRIPTION 
				"Description. fmnPlus1MTRFProgramPresent notification"
			::= { fmEventsnPlus1 12 }

		
		-- 1.3.6.1.4.1.19831.1.1.3.5.0.13
		fmnPlus1RTOpModeEvent NOTIFICATION-TYPE
			OBJECTS { sysDescr, sysName, sysLocation, eventTimeStamp, eventPriority, 
				eventCounter, fmnPlus1RTOpMode }
			STATUS current
			DESCRIPTION 
				"Description. fmnPlus1RTOpMode notification"
			::= { fmEventsnPlus1 13 }

		
		-- 1.3.6.1.4.1.19831.1.1.3.5.0.14
		fmnPlus1RTRFProgramPresentEvent NOTIFICATION-TYPE
			OBJECTS { sysDescr, sysName, sysLocation, eventTimeStamp, eventPriority, 
				eventCounter, fmnPlus1RTRFProgramPresent }
			STATUS current
			DESCRIPTION 
				"Description. fmnPlus1RTRFProgramPresent notification"
			::= { fmEventsnPlus1 14 }

		
		-- 1.3.6.1.4.1.19831.1.1.3.5.0.15
		fmnPlus1TARFPresentEvent NOTIFICATION-TYPE
			OBJECTS { sysDescr, sysName, sysLocation, eventTimeStamp, eventPriority, 
				eventCounter, fmnPlus1TARFPresent, fmnPlus1EventTransmitterIndex }
			STATUS current
			DESCRIPTION 
				"Description. fmnPlus1TARFPresent notification"
			::= { fmEventsnPlus1 15 }

		
		-- 1.3.6.1.4.1.19831.1.1.3.5.0.16
		fmnPlus1TALocalModeEvent NOTIFICATION-TYPE
			OBJECTS { sysDescr, sysName, sysLocation, eventTimeStamp, eventPriority, 
				eventCounter, fmnPlus1TALocalMode, fmnPlus1EventTransmitterIndex }
			STATUS current
			DESCRIPTION 
				"Description. fmnPlus1TALocalMode notification"
			::= { fmEventsnPlus1 16 }

		
		-- 1.3.6.1.4.1.19831.1.1.3.5.0.17
		fmnPlus1TAFaultEvent NOTIFICATION-TYPE
			OBJECTS { sysDescr, sysName, sysLocation, eventTimeStamp, eventPriority, 
				eventCounter, fmnPlus1TAFault, fmnPlus1EventTransmitterIndex }
			STATUS current
			DESCRIPTION 
				"Description. fmnPlus1TAFault notification"
			::= { fmEventsnPlus1 17 }

		
		-- 1.3.6.1.4.1.19831.1.1.3.5.0.18
		fmnPlus1TAWarningEvent NOTIFICATION-TYPE
			OBJECTS { sysDescr, sysName, sysLocation, eventTimeStamp, eventPriority, 
				eventCounter, fmnPlus1TAWarning, fmnPlus1EventTransmitterIndex }
			STATUS current
			DESCRIPTION 
				"Description. fmnPlus1TAWarning notification"
			::= { fmEventsnPlus1 18 }

		
		-- 1.3.6.1.4.1.19831.1.1.3.5.0.19
		fmnPlus1TBRFPresentEvent NOTIFICATION-TYPE
			OBJECTS { sysDescr, sysName, sysLocation, eventTimeStamp, eventPriority, 
				eventCounter, fmnPlus1TBRFPresent }
			STATUS current
			DESCRIPTION 
				"Description. fmnPlus1TBRFPresent notification"
			::= { fmEventsnPlus1 19 }

		
		-- 1.3.6.1.4.1.19831.1.1.3.5.0.20
		fmnPlus1TBLocalModeEvent NOTIFICATION-TYPE
			OBJECTS { sysDescr, sysName, sysLocation, eventTimeStamp, eventPriority, 
				eventCounter, fmnPlus1TBLocalMode }
			STATUS current
			DESCRIPTION 
				"Description. fmnPlus1TBLocalMode notification"
			::= { fmEventsnPlus1 20 }

		
		-- 1.3.6.1.4.1.19831.1.1.3.5.0.21
		fmnPlus1TBFaultEvent NOTIFICATION-TYPE
			OBJECTS { sysDescr, sysName, sysLocation, eventTimeStamp, eventPriority, 
				eventCounter, fmnPlus1TBFault }
			STATUS current
			DESCRIPTION 
				"Description. fmnPlus1TBFault notification"
			::= { fmEventsnPlus1 21 }

		
		-- 1.3.6.1.4.1.19831.1.1.3.5.0.22
		fmnPlus1TBWarningEvent NOTIFICATION-TYPE
			OBJECTS { sysDescr, sysName, sysLocation, eventTimeStamp, eventPriority, 
				eventCounter, fmnPlus1TBWarning }
			STATUS current
			DESCRIPTION 
				"Description. fmnPlus1TBWarning notification"
			::= { fmEventsnPlus1 22 }

		
-- fm N+1 Resreve. General
		-- 1.3.6.1.4.1.19831.1.1.3.5.1
		fmnPlus1General OBJECT IDENTIFIER ::= { fmnPlus1 1 }

		
		-- 1.3.6.1.4.1.19831.1.1.3.5.1.1
		fmnPlus1RedundancySwitchOver OBJECT-TYPE
			SYNTAX INTEGER (-1..12)
			MAX-ACCESS read-write
			STATUS current
			DESCRIPTION
				"N+1 reserve. Redundancy reserve switch over for transmitters B,A1,A2...An
				
				<-1,0,1,2,3,4,...,n>
				
				(-1) reserve transmitterB
				(0) undefined
				(1) transmitter 1
				(2) transmitter 2
				(3) transmitter 3
				(4) transmitter 4
				................
				(n) transmitter n"
			::= { fmnPlus1General 1 }

		
		-- 1.3.6.1.4.1.19831.1.1.3.5.1.2
		fmnPlus1LocalMode OBJECT-TYPE
			SYNTAX LocalRemote
			MAX-ACCESS read-only
			STATUS current
			DESCRIPTION
				"N+1 reserve. Local mode
				
				(0) undefined
				(1) local
				(2) remote"
			::= { fmnPlus1General 2 }

		
		-- 1.3.6.1.4.1.19831.1.1.3.5.1.3
		fmnPlus1ControlUnitFault OBJECT-TYPE
			SYNTAX FaultOK
			MAX-ACCESS read-only
			STATUS current
			DESCRIPTION
				"N+1 reserve. State of the control unit
				
				(0) undefined
				(1) fault
				(2) ok"
			::= { fmnPlus1General 3 }

		
		-- 1.3.6.1.4.1.19831.1.1.3.5.1.4
		fmnPlus1SwitchOverMode OBJECT-TYPE
			SYNTAX SelectManualAuto
			MAX-ACCESS read-write
			STATUS current
			DESCRIPTION
				"N+1 reserve. Switch over mode: manual or automatic
				
				(0) undefined
				(1) manual 
				(2) automatic"
			::= { fmnPlus1General 4 }

		
		-- 1.3.6.1.4.1.19831.1.1.3.5.1.5
		fmnPlus1SwitchOverReady OBJECT-TYPE
			SYNTAX ReadyNotReady
			MAX-ACCESS read-only
			STATUS current
			DESCRIPTION
				"State of the N+1 reserve  switch over unit
				
				(0) undefined
				(1) ready
				(2) not ready"
			::= { fmnPlus1General 5 }

		
		-- 1.3.6.1.4.1.19831.1.1.3.5.1.6
		fmnPlus1SwitchOverExecuted OBJECT-TYPE
			SYNTAX ExecutedNotExecuted
			MAX-ACCESS read-only
			STATUS current
			DESCRIPTION
				"N+1 reserve. Shows if the reserve switsch over uinit it has executed
				
				(0) undefined
				(1) executed
				(2) not executed"
			::= { fmnPlus1General 6 }

		
		-- 1.3.6.1.4.1.19831.1.1.3.5.1.7
		fmnPlus1SwitchOverFault OBJECT-TYPE
			SYNTAX FaultOK
			MAX-ACCESS read-only
			STATUS current
			DESCRIPTION
				"N+1 reserve. Fault state of the switch over unit
				
				(0) undefined
				(1) faulty
				(2) ok"
			::= { fmnPlus1General 7 }

		
		-- 1.3.6.1.4.1.19831.1.1.3.5.1.8
		fmnPlus1ChannelSelection OBJECT-TYPE
			SYNTAX Unsigned32
			MAX-ACCESS read-write
			STATUS current
			DESCRIPTION
				"N+1 reserve. Chanel selection 1...n of reserve transmitter
				
				<0,1,2,...,n>
				
				(0) undefined
				(1) chanel 1
				(2) chanel 2
				...
				(n) chanel n
				
				"
			::= { fmnPlus1General 8 }

		
		-- 1.3.6.1.4.1.19831.1.1.3.5.1.9
		fmnPlus1TransmitterBReset OBJECT-TYPE
			SYNTAX Unsigned32
			MAX-ACCESS read-write
			STATUS obsolete
			DESCRIPTION
				"Message is not active!
				
				N+1 Reserve. Transmitter B reset: trigger for reset 
				
				<1>
				
				(1) reset fault
				"
			::= { fmnPlus1General 9 }

		
		-- 1.3.6.1.4.1.19831.1.1.3.5.1.10
		fmnPlus1TransmitterBMode OBJECT-TYPE
			SYNTAX TransmitterBFreeOccupied
			MAX-ACCESS read-only
			STATUS obsolete
			DESCRIPTION
				"Message is not active!
				
				N+1 reserve. Transmitter B redundancy state
				
				(1) free
				(2) occupied
				"
			::= { fmnPlus1General 10 }

		
		-- 1.3.6.1.4.1.19831.1.1.3.5.1.11
		fmnPlus1EventTransmitterIndex OBJECT-TYPE
			SYNTAX Unsigned32 (1..255)
			MAX-ACCESS read-only
			STATUS current
			DESCRIPTION
				"N+1 reserve. Event index to be transmitted along which each trap from MaintransmitterTable or TransmitterATable"
			::= { fmnPlus1General 11 }

		
-- fm N+1 reserve. Main transmitter table
		-- 1.3.6.1.4.1.19831.1.1.3.5.2
		fmnPlus1MainTransmitterTable OBJECT-TYPE
			SYNTAX SEQUENCE OF FmnPlus1MainTransmitterEntry
			MAX-ACCESS not-accessible
			STATUS current
			DESCRIPTION
				"Table of logical transmitters carrying programs
				"
			::= { fmnPlus1 2 }

		
-- dvb N+1 reserve: One logical transmitter, numbered from 1 to n
		-- 1.3.6.1.4.1.19831.1.1.3.5.2.1
		fmnPlus1MainTransmitterEntry OBJECT-TYPE
			SYNTAX FmnPlus1MainTransmitterEntry
			MAX-ACCESS not-accessible
			STATUS current
			DESCRIPTION
				"One logical transmitter, numbered from 1 to n"
			INDEX { fmnPlus1MTIndex }
			::= { fmnPlus1MainTransmitterTable 1 }

		
		FmnPlus1MainTransmitterEntry ::=
			SEQUENCE { 
				fmnPlus1MTIndex
					Unsigned32,
				fmnPlus1MTOpMode
					SelectOnOff,
				fmnPlus1MTRFProgramPresent
					PresentNotPresent
			 }

		-- 1.3.6.1.4.1.19831.1.1.3.5.2.1.1
		fmnPlus1MTIndex OBJECT-TYPE
			SYNTAX Unsigned32 (1..255)
			MAX-ACCESS read-only
			STATUS current
			DESCRIPTION
				"N+1 Reserve. Main transmitter index
				
				<1,2,3,4,5,6,7,8,9>
				
				(1) transmitter 1
				(2) transmitter 2
				(3) transmitter 3
				(4) transmitter 4
				(5) transmitter 5
				(6) transmitter 6
				(7) transmitter 7
				(8) transmitter 8
				(9) transmitter 9
				"
			::= { fmnPlus1MainTransmitterEntry 1 }

		
		-- 1.3.6.1.4.1.19831.1.1.3.5.2.1.2
		fmnPlus1MTOpMode OBJECT-TYPE
			SYNTAX SelectOnOff
			MAX-ACCESS read-write
			STATUS current
			DESCRIPTION
				"N+1 Reserve. General transmitter control 
				
				(0) undefined
				(1) ON
				(2) OFF"
			::= { fmnPlus1MainTransmitterEntry 2 }

		
		-- 1.3.6.1.4.1.19831.1.1.3.5.2.1.3
		fmnPlus1MTRFProgramPresent OBJECT-TYPE
			SYNTAX PresentNotPresent
			MAX-ACCESS read-only
			STATUS current
			DESCRIPTION
				"N+1 reserve. Describes if the output power of the   main transmitter is present
				
				(0) undefined
				(1) present
				(2) not present"
			::= { fmnPlus1MainTransmitterEntry 3 }

		
-- fm N+1 reserve. Reserve Transmitter
		-- 1.3.6.1.4.1.19831.1.1.3.5.3
		fmnPlus1ReserveTransmitter OBJECT IDENTIFIER ::= { fmnPlus1 3 }

		
		-- 1.3.6.1.4.1.19831.1.1.3.5.3.2
		fmnPlus1RTOpMode OBJECT-TYPE
			SYNTAX SelectOnOff
			MAX-ACCESS read-write
			STATUS current
			DESCRIPTION
				"N+1 reserve. reserve transmitter control
				
				(0) undefined
				(1) ON
				(2) OFF"
			::= { fmnPlus1ReserveTransmitter 2 }

		
		-- 1.3.6.1.4.1.19831.1.1.3.5.3.3
		fmnPlus1RTRFProgramPresent OBJECT-TYPE
			SYNTAX PresentNotPresent
			MAX-ACCESS read-only
			STATUS current
			DESCRIPTION
				"N+1 reserve. Describes if the output power of the   reserve transmitter is present
				
				(0) undefined
				(1) present
				(2) not present"
			::= { fmnPlus1ReserveTransmitter 3 }

		
-- fm N+1 reserve. Transmitter A table
		-- 1.3.6.1.4.1.19831.1.1.3.5.4
		fmnPlus1TransmitterATable OBJECT-TYPE
			SYNTAX SEQUENCE OF FmnPlus1TransmitterAEntry
			MAX-ACCESS not-accessible
			STATUS current
			DESCRIPTION
				"Table of physical transmitters ment to be on air in normal operation"
			::= { fmnPlus1 4 }

		
-- dvb n+1 reserve: transmitter A entry - rows
		-- 1.3.6.1.4.1.19831.1.1.3.5.4.1
		fmnPlus1TransmitterAEntry OBJECT-TYPE
			SYNTAX FmnPlus1TransmitterAEntry
			MAX-ACCESS not-accessible
			STATUS current
			DESCRIPTION
				"N+1 reserve. One physical transmitter, numbered from A1 to An"
			INDEX { fmnPlus1TAIndex }
			::= { fmnPlus1TransmitterATable 1 }

		
		FmnPlus1TransmitterAEntry ::=
			SEQUENCE { 
				fmnPlus1TAIndex
					Unsigned32,
				fmnPlus1TARFPresent
					PresentNotPresent,
				fmnPlus1TALocalMode
					LocalRemote,
				fmnPlus1TAFault
					FaultOK,
				fmnPlus1TAWarning
					WarningOK
			 }

		-- 1.3.6.1.4.1.19831.1.1.3.5.4.1.1
		fmnPlus1TAIndex OBJECT-TYPE
			SYNTAX Unsigned32 (1..255)
			MAX-ACCESS read-only
			STATUS current
			DESCRIPTION
				"N+1 reserve. Index of the  transmitters A1,A2...An
				
				"
			::= { fmnPlus1TransmitterAEntry 1 }

		
		-- 1.3.6.1.4.1.19831.1.1.3.5.4.1.2
		fmnPlus1TARFPresent OBJECT-TYPE
			SYNTAX PresentNotPresent
			MAX-ACCESS read-only
			STATUS current
			DESCRIPTION
				"N+1 reserve. Describes if the output power of the  transmitter A is present
				
				(0) undefined
				(1) present
				(2) not present"
			::= { fmnPlus1TransmitterAEntry 2 }

		
		-- 1.3.6.1.4.1.19831.1.1.3.5.4.1.3
		fmnPlus1TALocalMode OBJECT-TYPE
			SYNTAX LocalRemote
			MAX-ACCESS read-only
			STATUS current
			DESCRIPTION
				"N+1 reserve. Local mode of the  transmitter A
				
				(0) undefined
				(1) local
				(2) remote"
			::= { fmnPlus1TransmitterAEntry 3 }

		
		-- 1.3.6.1.4.1.19831.1.1.3.5.4.1.4
		fmnPlus1TAFault OBJECT-TYPE
			SYNTAX FaultOK
			MAX-ACCESS read-only
			STATUS current
			DESCRIPTION
				"N+1 reserve. Fault state of the transmitter A
				
				(0) undefined
				(1) fault
				(2) ok"
			::= { fmnPlus1TransmitterAEntry 4 }

		
		-- 1.3.6.1.4.1.19831.1.1.3.5.4.1.5
		fmnPlus1TAWarning OBJECT-TYPE
			SYNTAX WarningOK
			MAX-ACCESS read-only
			STATUS current
			DESCRIPTION
				"N+1 reserve. Warning state of transmiter A
				
				(0) undefined
				(1) warning
				(2) ok"
			::= { fmnPlus1TransmitterAEntry 5 }

		
-- fm N+1. Transmitter B
		-- 1.3.6.1.4.1.19831.1.1.3.5.5
		fmnPlus1TransmitterB OBJECT IDENTIFIER ::= { fmnPlus1 5 }

		
		-- 1.3.6.1.4.1.19831.1.1.3.5.5.2
		fmnPlus1TBRFPresent OBJECT-TYPE
			SYNTAX PresentNotPresent
			MAX-ACCESS read-only
			STATUS current
			DESCRIPTION
				"n+1 reserve:  Describes if the output power of the  transmitter B is present
				
				(0) undefined
				(1) present
				(2) not present"
			::= { fmnPlus1TransmitterB 2 }

		
		-- 1.3.6.1.4.1.19831.1.1.3.5.5.3
		fmnPlus1TBLocalMode OBJECT-TYPE
			SYNTAX LocalRemote
			MAX-ACCESS read-only
			STATUS current
			DESCRIPTION
				"N+1 reserve. Reserve local mode: Describes the output Power of the  transmitter B
				
				(0) undefined
				(1) local
				(2) remote"
			::= { fmnPlus1TransmitterB 3 }

		
		-- 1.3.6.1.4.1.19831.1.1.3.5.5.4
		fmnPlus1TBFault OBJECT-TYPE
			SYNTAX FaultOK
			MAX-ACCESS read-only
			STATUS current
			DESCRIPTION
				"N+1 reserve. Fault state of reserve 
				
				(0) undefined
				(1) fault
				(2) ok"
			::= { fmnPlus1TransmitterB 4 }

		
		-- 1.3.6.1.4.1.19831.1.1.3.5.5.5
		fmnPlus1TBWarning OBJECT-TYPE
			SYNTAX WarningOK
			MAX-ACCESS read-only
			STATUS current
			DESCRIPTION
				"n+1 reserve. Warning state of reserve
				
				(0) undefined
				(1) warning
				(2) ok"
			::= { fmnPlus1TransmitterB 5 }

		
-- fm N+1 reserve. Switch for event 
		-- 1.3.6.1.4.1.19831.1.1.3.5.6
		fmnPlus1EventEnable OBJECT IDENTIFIER ::= { fmnPlus1 6 }

		
-- dvb N+1 reserve. general:  events 
		-- 1.3.6.1.4.1.19831.1.1.3.5.6.1
		fmnPlus1EventEnableGeneral OBJECT IDENTIFIER ::= { fmnPlus1EventEnable 1 }

		
		-- 1.3.6.1.4.1.19831.1.1.3.5.6.1.1
		fmnPlus1RedundancySwitchOverEnable OBJECT-TYPE
			SYNTAX TruthValue
			MAX-ACCESS read-write
			STATUS current
			DESCRIPTION
				"Description. Enable/Disable switch for fmnPlus1RedundancySwitchOve event"
			::= { fmnPlus1EventEnableGeneral 1 }

		
		-- 1.3.6.1.4.1.19831.1.1.3.5.6.1.2
		fmnPlus1LocalModeEnable OBJECT-TYPE
			SYNTAX TruthValue
			MAX-ACCESS read-write
			STATUS current
			DESCRIPTION
				"Description. Enable/Disable switch for fmnPlus1LocalMode event"
			::= { fmnPlus1EventEnableGeneral 2 }

		
		-- 1.3.6.1.4.1.19831.1.1.3.5.6.1.3
		fmnPlus1ControlUnitFaultEnable OBJECT-TYPE
			SYNTAX TruthValue
			MAX-ACCESS read-write
			STATUS current
			DESCRIPTION
				"Description. Enable/Disable switch for fmnPlus1ControlUnitFault event"
			::= { fmnPlus1EventEnableGeneral 3 }

		
		-- 1.3.6.1.4.1.19831.1.1.3.5.6.1.4
		fmnPlus1SwitchOverModeEnable OBJECT-TYPE
			SYNTAX TruthValue
			MAX-ACCESS read-write
			STATUS current
			DESCRIPTION
				"Description. Enable/Disable switch for fmnPlus1SwitchOverMode event"
			::= { fmnPlus1EventEnableGeneral 4 }

		
		-- 1.3.6.1.4.1.19831.1.1.3.5.6.1.5
		fmnPlus1SwitchOverReadyEnable OBJECT-TYPE
			SYNTAX TruthValue
			MAX-ACCESS read-write
			STATUS current
			DESCRIPTION
				"Description. Enable/Disable switch for fmnPlus1SwitchOverReady event"
			::= { fmnPlus1EventEnableGeneral 5 }

		
		-- 1.3.6.1.4.1.19831.1.1.3.5.6.1.6
		fmnPlus1SwitchOverExecutedEnable OBJECT-TYPE
			SYNTAX TruthValue
			MAX-ACCESS read-write
			STATUS current
			DESCRIPTION
				"Description. Enable/Disable switch for fmnPlus1SwitchOverExecuted event"
			::= { fmnPlus1EventEnableGeneral 6 }

		
		-- 1.3.6.1.4.1.19831.1.1.3.5.6.1.7
		fmnPlus1SwitchOverFaultEnable OBJECT-TYPE
			SYNTAX TruthValue
			MAX-ACCESS read-write
			STATUS current
			DESCRIPTION
				"Description. Enable/Disable switch for fmnPlus1SwitchOverFault event"
			::= { fmnPlus1EventEnableGeneral 7 }

		
		-- 1.3.6.1.4.1.19831.1.1.3.5.6.1.8
		fmnPlus1ChannelSelectionEnable OBJECT-TYPE
			SYNTAX TruthValue
			MAX-ACCESS read-write
			STATUS current
			DESCRIPTION
				"Description. Enable/Disable switch for fmnPlus1ChannelSelection event"
			::= { fmnPlus1EventEnableGeneral 8 }

		
		-- 1.3.6.1.4.1.19831.1.1.3.5.6.1.9
		fmnPlus1TransmitterBResetEnable OBJECT-TYPE
			SYNTAX TruthValue
			MAX-ACCESS read-write
			STATUS obsolete
			DESCRIPTION
				"Message is not active!
				
				Description. Enable/Disable switch for fmnPlus1TransmitterBReset event"
			::= { fmnPlus1EventEnableGeneral 9 }

		
		-- 1.3.6.1.4.1.19831.1.1.3.5.6.1.10
		fmnPlus1TransmitterBModeEnable OBJECT-TYPE
			SYNTAX TruthValue
			MAX-ACCESS read-write
			STATUS obsolete
			DESCRIPTION
				"Message is not active!
				
				Description. Enable/Disable switch for fmnPlus1TransmitterBMode event"
			::= { fmnPlus1EventEnableGeneral 10 }

		
-- fm N+1 reserve. main transmitter table: events 
		-- 1.3.6.1.4.1.19831.1.1.3.5.6.2
		fmnPlus1EventEnableMainTransmitterTable OBJECT-TYPE
			SYNTAX SEQUENCE OF FmnPlus1EventEnableMainTransmitterEntry
			MAX-ACCESS not-accessible
			STATUS current
			DESCRIPTION
				"fm N+1 reserve. Transmitters main transmitter table: switch for events 
				"
			::= { fmnPlus1EventEnable 2 }

		
-- fm N+1 reserve: Main transmitter table rows
		-- 1.3.6.1.4.1.19831.1.1.3.5.6.2.1
		fmnPlus1EventEnableMainTransmitterEntry OBJECT-TYPE
			SYNTAX FmnPlus1EventEnableMainTransmitterEntry
			MAX-ACCESS not-accessible
			STATUS current
			DESCRIPTION
				"One logical transmitter, numbered from 1 to n"
			INDEX { fmnPlus1MTIndex }
			::= { fmnPlus1EventEnableMainTransmitterTable 1 }

		
		FmnPlus1EventEnableMainTransmitterEntry ::=
			SEQUENCE { 
				fmnPlus1MTOpModeEnable
					TruthValue,
				fmnPlus1MTRFProgramPresentEnable
					TruthValue
			 }

		-- 1.3.6.1.4.1.19831.1.1.3.5.6.2.1.2
		fmnPlus1MTOpModeEnable OBJECT-TYPE
			SYNTAX TruthValue
			MAX-ACCESS read-write
			STATUS current
			DESCRIPTION
				"Description. Enable/Disable switch for fmnPlus1MTOpMode event"
			::= { fmnPlus1EventEnableMainTransmitterEntry 2 }

		
		-- 1.3.6.1.4.1.19831.1.1.3.5.6.2.1.3
		fmnPlus1MTRFProgramPresentEnable OBJECT-TYPE
			SYNTAX TruthValue
			MAX-ACCESS read-write
			STATUS current
			DESCRIPTION
				"Description. Enable/Disable switch for fmnPlus1MTRFProgramPresent event"
			::= { fmnPlus1EventEnableMainTransmitterEntry 3 }

		
-- fm N+1 reserve. reserve transmitter: events
		-- 1.3.6.1.4.1.19831.1.1.3.5.6.3
		fmnPlus1EventEnableReserveTransmitter OBJECT IDENTIFIER ::= { fmnPlus1EventEnable 3 }

		
		-- 1.3.6.1.4.1.19831.1.1.3.5.6.3.2
		fmnPlus1RTOpModeEnable OBJECT-TYPE
			SYNTAX TruthValue
			MAX-ACCESS read-write
			STATUS current
			DESCRIPTION
				"Description. Enable/Disable switch for fmnPlus1RTOpMode event"
			::= { fmnPlus1EventEnableReserveTransmitter 2 }

		
		-- 1.3.6.1.4.1.19831.1.1.3.5.6.3.3
		fmnPlus1RTRFProgramPresentEnable OBJECT-TYPE
			SYNTAX TruthValue
			MAX-ACCESS read-write
			STATUS current
			DESCRIPTION
				"Description. Enable/Disable switch for fmnPlus1RTRFProgramPresent event"
			::= { fmnPlus1EventEnableReserveTransmitter 3 }

		
-- fm N+1 reserve. Transmitters A table: events 
		-- 1.3.6.1.4.1.19831.1.1.3.5.6.4
		fmnPlus1EventEnableTransmitterATable OBJECT-TYPE
			SYNTAX SEQUENCE OF FmnPlus1EventEnableTransmitterAEntry
			MAX-ACCESS not-accessible
			STATUS current
			DESCRIPTION
				"fm n+1 reserve. Transmitters A table: switch for events "
			::= { fmnPlus1EventEnable 4 }

		
-- fm N+1 reserve: transmitter A entry - rows
		-- 1.3.6.1.4.1.19831.1.1.3.5.6.4.1
		fmnPlus1EventEnableTransmitterAEntry OBJECT-TYPE
			SYNTAX FmnPlus1EventEnableTransmitterAEntry
			MAX-ACCESS not-accessible
			STATUS current
			DESCRIPTION
				"One physical transmitter, numbered from A1 to An"
			INDEX { fmnPlus1TAIndex }
			::= { fmnPlus1EventEnableTransmitterATable 1 }

		
		FmnPlus1EventEnableTransmitterAEntry ::=
			SEQUENCE { 
				fmnPlus1TARFPresentEnable
					TruthValue,
				fmnPlus1TALocalModeEnable
					TruthValue,
				fmnPlus1TAFaultEnable
					TruthValue,
				fmnPlus1TAWarningEnable
					TruthValue
			 }

		-- 1.3.6.1.4.1.19831.1.1.3.5.6.4.1.2
		fmnPlus1TARFPresentEnable OBJECT-TYPE
			SYNTAX TruthValue
			MAX-ACCESS read-write
			STATUS current
			DESCRIPTION
				"Description. Enable/Disable switch for fmnPlus1TARFPresent event"
			::= { fmnPlus1EventEnableTransmitterAEntry 2 }

		
		-- 1.3.6.1.4.1.19831.1.1.3.5.6.4.1.3
		fmnPlus1TALocalModeEnable OBJECT-TYPE
			SYNTAX TruthValue
			MAX-ACCESS read-write
			STATUS current
			DESCRIPTION
				"Description. Enable/Disable switch for fmnPlus1TALocalMode event"
			::= { fmnPlus1EventEnableTransmitterAEntry 3 }

		
		-- 1.3.6.1.4.1.19831.1.1.3.5.6.4.1.4
		fmnPlus1TAFaultEnable OBJECT-TYPE
			SYNTAX TruthValue
			MAX-ACCESS read-write
			STATUS current
			DESCRIPTION
				"Description. Enable/Disable switch for fmnPlus1TAFault event"
			::= { fmnPlus1EventEnableTransmitterAEntry 4 }

		
		-- 1.3.6.1.4.1.19831.1.1.3.5.6.4.1.5
		fmnPlus1TAWarningEnable OBJECT-TYPE
			SYNTAX TruthValue
			MAX-ACCESS read-write
			STATUS current
			DESCRIPTION
				"Description. Enable/Disable switch for fmnPlus1TAWarning event"
			::= { fmnPlus1EventEnableTransmitterAEntry 5 }

		
-- fm N+1: transmitter B: events
		-- 1.3.6.1.4.1.19831.1.1.3.5.6.5
		fmnPlus1EventEnableTransmitterB OBJECT IDENTIFIER ::= { fmnPlus1EventEnable 5 }

		
		-- 1.3.6.1.4.1.19831.1.1.3.5.6.5.2
		fmnPlus1TBRFPresentEnable OBJECT-TYPE
			SYNTAX TruthValue
			MAX-ACCESS read-write
			STATUS current
			DESCRIPTION
				"Description. Enable/Disable switch for fmnPlus1TBRFPresent event"
			::= { fmnPlus1EventEnableTransmitterB 2 }

		
		-- 1.3.6.1.4.1.19831.1.1.3.5.6.5.3
		fmnPlus1TBLocalModeEnable OBJECT-TYPE
			SYNTAX TruthValue
			MAX-ACCESS read-write
			STATUS current
			DESCRIPTION
				"Description. Enable/Disable switch for fmnPlus1TBLocalMode event"
			::= { fmnPlus1EventEnableTransmitterB 3 }

		
		-- 1.3.6.1.4.1.19831.1.1.3.5.6.5.4
		fmnPlus1TBFaultEnable OBJECT-TYPE
			SYNTAX TruthValue
			MAX-ACCESS read-write
			STATUS current
			DESCRIPTION
				"Description. Enable/Disable switch for fmnPlus1TBFault event"
			::= { fmnPlus1EventEnableTransmitterB 4 }

		
		-- 1.3.6.1.4.1.19831.1.1.3.5.6.5.5
		fmnPlus1TBWarningEnable OBJECT-TYPE
			SYNTAX TruthValue
			MAX-ACCESS read-write
			STATUS current
			DESCRIPTION
				"Description. Enable/Disable switch for fmnPlus1TBWarning event"
			::= { fmnPlus1EventEnableTransmitterB 5 }

		
-- fm N+1 reserve. Event priority
		-- 1.3.6.1.4.1.19831.1.1.3.5.7
		fmnPlus1EventPriority OBJECT IDENTIFIER ::= { fmnPlus1 7 }

		
-- fm N+1 reserve: general: event priority
		-- 1.3.6.1.4.1.19831.1.1.3.5.7.1
		fmnPlus1EventPriorityGeneral OBJECT IDENTIFIER ::= { fmnPlus1EventPriority 1 }

		
		-- 1.3.6.1.4.1.19831.1.1.3.5.7.1.1
		fmnPlus1RedundancySwitchOverPriority OBJECT-TYPE
			SYNTAX Unsigned32
			MAX-ACCESS read-write
			STATUS current
			DESCRIPTION
				"Priority switch for fmnPlus1RedundancySwitchOver event"
			::= { fmnPlus1EventPriorityGeneral 1 }

		
		-- 1.3.6.1.4.1.19831.1.1.3.5.7.1.2
		fmnPlus1LocalModePriority OBJECT-TYPE
			SYNTAX Unsigned32
			MAX-ACCESS read-write
			STATUS current
			DESCRIPTION
				"Priority switch for fmnPlus1LocalMode event"
			::= { fmnPlus1EventPriorityGeneral 2 }

		
		-- 1.3.6.1.4.1.19831.1.1.3.5.7.1.3
		fmnPlus1ControlUnitFaultPriority OBJECT-TYPE
			SYNTAX Unsigned32
			MAX-ACCESS read-write
			STATUS current
			DESCRIPTION
				"Priority switch for fmnPlus1ControlUnitFault event"
			::= { fmnPlus1EventPriorityGeneral 3 }

		
		-- 1.3.6.1.4.1.19831.1.1.3.5.7.1.4
		fmnPlus1SwitchOverModePriority OBJECT-TYPE
			SYNTAX Unsigned32
			MAX-ACCESS read-write
			STATUS current
			DESCRIPTION
				"Priority switch for fmnPlus1SwitchOverMode event"
			::= { fmnPlus1EventPriorityGeneral 4 }

		
		-- 1.3.6.1.4.1.19831.1.1.3.5.7.1.5
		fmnPlus1SwitchOverReadyPriority OBJECT-TYPE
			SYNTAX Unsigned32
			MAX-ACCESS read-write
			STATUS current
			DESCRIPTION
				"Priority switch for fmnPlus1SwitchOverReady event"
			::= { fmnPlus1EventPriorityGeneral 5 }

		
		-- 1.3.6.1.4.1.19831.1.1.3.5.7.1.6
		fmnPlus1SwitchOverExecutedPriority OBJECT-TYPE
			SYNTAX Unsigned32
			MAX-ACCESS read-write
			STATUS current
			DESCRIPTION
				"Priority switch for fmnPlus1SwitchOverExecuted event"
			::= { fmnPlus1EventPriorityGeneral 6 }

		
		-- 1.3.6.1.4.1.19831.1.1.3.5.7.1.7
		fmnPlus1SwitchOverFaultPriority OBJECT-TYPE
			SYNTAX Unsigned32
			MAX-ACCESS read-write
			STATUS current
			DESCRIPTION
				"Priority switch for fmnPlus1SwitchOverFault event"
			::= { fmnPlus1EventPriorityGeneral 7 }

		
		-- 1.3.6.1.4.1.19831.1.1.3.5.7.1.8
		fmnPlus1ChannelSelectionPriority OBJECT-TYPE
			SYNTAX Unsigned32
			MAX-ACCESS read-write
			STATUS current
			DESCRIPTION
				"Priority switch for fmnPlus1RChanelSelection event"
			::= { fmnPlus1EventPriorityGeneral 8 }

		
		-- 1.3.6.1.4.1.19831.1.1.3.5.7.1.9
		fmnPlus1TransmitterBResetPriority OBJECT-TYPE
			SYNTAX Unsigned32
			MAX-ACCESS read-write
			STATUS obsolete
			DESCRIPTION
				"Message is not active!
				
				Priority switch for fmnPlus1TransmitterBReset event"
			::= { fmnPlus1EventPriorityGeneral 9 }

		
		-- 1.3.6.1.4.1.19831.1.1.3.5.7.1.10
		fmnPlus1TransmitterBModePriority OBJECT-TYPE
			SYNTAX Unsigned32
			MAX-ACCESS read-write
			STATUS obsolete
			DESCRIPTION
				"Message is not active!
				
				Priority switch for fmnPlus1TransmitterBMode event"
			::= { fmnPlus1EventPriorityGeneral 10 }

		
-- fm N+1 reserve: Main transmitter table: event priority
		-- 1.3.6.1.4.1.19831.1.1.3.5.7.2
		fmnPlus1EventPriorityMainTransmitterTable OBJECT-TYPE
			SYNTAX SEQUENCE OF FmnPlus1EventPriorityMainTransmitterEntry
			MAX-ACCESS not-accessible
			STATUS current
			DESCRIPTION
				"dvb n+1 reserve. general: priority for event"
			::= { fmnPlus1EventPriority 2 }

		
-- fm N+1 reserve: Main transmitter table rows
		-- 1.3.6.1.4.1.19831.1.1.3.5.7.2.1
		fmnPlus1EventPriorityMainTransmitterEntry OBJECT-TYPE
			SYNTAX FmnPlus1EventPriorityMainTransmitterEntry
			MAX-ACCESS not-accessible
			STATUS current
			DESCRIPTION
				"One logical transmitter, numbered from 1 to n"
			INDEX { fmnPlus1MTIndex }
			::= { fmnPlus1EventPriorityMainTransmitterTable 1 }

		
		FmnPlus1EventPriorityMainTransmitterEntry ::=
			SEQUENCE { 
				fmnPlus1MTOpModePriority
					Unsigned32,
				fmnPlus1MTRFProgramPresentPriority
					Unsigned32
			 }

		-- 1.3.6.1.4.1.19831.1.1.3.5.7.2.1.2
		fmnPlus1MTOpModePriority OBJECT-TYPE
			SYNTAX Unsigned32
			MAX-ACCESS read-write
			STATUS current
			DESCRIPTION
				"Priority switch for fmnPlus1MTOpMode event"
			::= { fmnPlus1EventPriorityMainTransmitterEntry 2 }

		
		-- 1.3.6.1.4.1.19831.1.1.3.5.7.2.1.3
		fmnPlus1MTRFProgramPresentPriority OBJECT-TYPE
			SYNTAX Unsigned32
			MAX-ACCESS read-write
			STATUS current
			DESCRIPTION
				"Priority switch for fmnPlus1MTRFProgramPresent event"
			::= { fmnPlus1EventPriorityMainTransmitterEntry 3 }

		
-- fm N+1 reserve. Reserve transmitter: event priority
		-- 1.3.6.1.4.1.19831.1.1.3.5.7.3
		fmnPlus1EventPriorityReserveTransmitter OBJECT IDENTIFIER ::= { fmnPlus1EventPriority 3 }

		
		-- 1.3.6.1.4.1.19831.1.1.3.5.7.3.2
		fmnPlus1RTOpModePriority OBJECT-TYPE
			SYNTAX Unsigned32
			MAX-ACCESS read-write
			STATUS current
			DESCRIPTION
				"Priority switch for fmnPlus1RTOpMode event"
			::= { fmnPlus1EventPriorityReserveTransmitter 2 }

		
		-- 1.3.6.1.4.1.19831.1.1.3.5.7.3.3
		fmnPlus1RTRFProgramPresentPriority OBJECT-TYPE
			SYNTAX Unsigned32
			MAX-ACCESS read-write
			STATUS current
			DESCRIPTION
				"Priority switch for fmnPlus1RTRFProgramPresent event"
			::= { fmnPlus1EventPriorityReserveTransmitter 3 }

		
-- fm N+1 reserve. Transmitter A table: event priority
		-- 1.3.6.1.4.1.19831.1.1.3.5.7.4
		fmnPlus1EventPriorityTransmitterATable OBJECT-TYPE
			SYNTAX SEQUENCE OF FmnPlus1EventPriorityTransmitterAEntry
			MAX-ACCESS not-accessible
			STATUS current
			DESCRIPTION
				"dvb n+1 reserve. transmitter A table: priority for event"
			::= { fmnPlus1EventPriority 4 }

		
-- fm N+1 reserve. Transmitter A entry - rows
		-- 1.3.6.1.4.1.19831.1.1.3.5.7.4.1
		fmnPlus1EventPriorityTransmitterAEntry OBJECT-TYPE
			SYNTAX FmnPlus1EventPriorityTransmitterAEntry
			MAX-ACCESS not-accessible
			STATUS current
			DESCRIPTION
				"One physical transmitter, numbered from A1 to An"
			INDEX { fmnPlus1TAIndex }
			::= { fmnPlus1EventPriorityTransmitterATable 1 }

		
		FmnPlus1EventPriorityTransmitterAEntry ::=
			SEQUENCE { 
				fmnPlus1TARFPresentPriority
					Unsigned32,
				fmnPlus1TALocalModePriority
					Unsigned32,
				fmnPlus1TAFaultPriority
					Unsigned32,
				fmnPlus1TAWarningPriority
					Unsigned32
			 }

		-- 1.3.6.1.4.1.19831.1.1.3.5.7.4.1.2
		fmnPlus1TARFPresentPriority OBJECT-TYPE
			SYNTAX Unsigned32
			MAX-ACCESS read-write
			STATUS current
			DESCRIPTION
				"Priority switch for fmnPlus1TARFPresent event"
			::= { fmnPlus1EventPriorityTransmitterAEntry 2 }

		
		-- 1.3.6.1.4.1.19831.1.1.3.5.7.4.1.3
		fmnPlus1TALocalModePriority OBJECT-TYPE
			SYNTAX Unsigned32
			MAX-ACCESS read-write
			STATUS current
			DESCRIPTION
				"Priority switch for fmnPlus1TALocalModer event"
			::= { fmnPlus1EventPriorityTransmitterAEntry 3 }

		
		-- 1.3.6.1.4.1.19831.1.1.3.5.7.4.1.4
		fmnPlus1TAFaultPriority OBJECT-TYPE
			SYNTAX Unsigned32
			MAX-ACCESS read-write
			STATUS current
			DESCRIPTION
				"Priority switch for fmnPlus1TAFaultPriority event"
			::= { fmnPlus1EventPriorityTransmitterAEntry 4 }

		
		-- 1.3.6.1.4.1.19831.1.1.3.5.7.4.1.5
		fmnPlus1TAWarningPriority OBJECT-TYPE
			SYNTAX Unsigned32
			MAX-ACCESS read-write
			STATUS current
			DESCRIPTION
				"Priority switch for fmnPlus1TAWarning event"
			::= { fmnPlus1EventPriorityTransmitterAEntry 5 }

		
-- fm N+1. Tansmitter B event priority
		-- 1.3.6.1.4.1.19831.1.1.3.5.7.5
		fmnPlus1EventPriorityTransmitterB OBJECT IDENTIFIER ::= { fmnPlus1EventPriority 5 }

		
		-- 1.3.6.1.4.1.19831.1.1.3.5.7.5.2
		fmnPlus1TBRFPresentPriority OBJECT-TYPE
			SYNTAX Unsigned32
			MAX-ACCESS read-write
			STATUS current
			DESCRIPTION
				"Priority switch for fmnPlus1TBRFPresent event"
			::= { fmnPlus1EventPriorityTransmitterB 2 }

		
		-- 1.3.6.1.4.1.19831.1.1.3.5.7.5.3
		fmnPlus1TBLocalModePriority OBJECT-TYPE
			SYNTAX Unsigned32
			MAX-ACCESS read-write
			STATUS current
			DESCRIPTION
				"Priority switch for fmnPlus1TBLocalMode event"
			::= { fmnPlus1EventPriorityTransmitterB 3 }

		
		-- 1.3.6.1.4.1.19831.1.1.3.5.7.5.4
		fmnPlus1TBFaultPriority OBJECT-TYPE
			SYNTAX Unsigned32
			MAX-ACCESS read-write
			STATUS current
			DESCRIPTION
				"Priority switch for fmnPlus1TBFault event"
			::= { fmnPlus1EventPriorityTransmitterB 4 }

		
		-- 1.3.6.1.4.1.19831.1.1.3.5.7.5.5
		fmnPlus1TBWarningPriority OBJECT-TYPE
			SYNTAX Unsigned32
			MAX-ACCESS read-write
			STATUS current
			DESCRIPTION
				"Priority switch for fmnPlus1TBWarning event"
			::= { fmnPlus1EventPriorityTransmitterB 5 }

		
		-- 1.3.6.1.4.1.19831.1.1.3.5.8
		groupsnPlus1 OBJECT IDENTIFIER ::= { fmnPlus1 8 }

		
		-- 1.3.6.1.4.1.19831.1.1.3.5.8.1
		objectGroupnPlus1 OBJECT-GROUP
			OBJECTS { fmnPlus1RedundancySwitchOver, fmnPlus1LocalMode, fmnPlus1ControlUnitFault, fmnPlus1SwitchOverMode, fmnPlus1SwitchOverReady, 
				fmnPlus1SwitchOverExecuted, fmnPlus1SwitchOverFault, fmnPlus1ChannelSelection, fmnPlus1EventTransmitterIndex, fmnPlus1MTIndex, 
				fmnPlus1MTRFProgramPresent, fmnPlus1RTOpMode, fmnPlus1RTRFProgramPresent, fmnPlus1TAIndex, fmnPlus1TARFPresent, 
				fmnPlus1TAFault, fmnPlus1TAWarning, fmnPlus1TBRFPresent, fmnPlus1TBFault, fmnPlus1TBWarning, 
				fmnPlus1RedundancySwitchOverEnable, fmnPlus1LocalModeEnable, fmnPlus1ControlUnitFaultEnable, fmnPlus1SwitchOverModeEnable, fmnPlus1SwitchOverReadyEnable, 
				fmnPlus1SwitchOverExecutedEnable, fmnPlus1SwitchOverFaultEnable, fmnPlus1ChannelSelectionEnable, fmnPlus1MTRFProgramPresentEnable, fmnPlus1RTOpModeEnable, 
				fmnPlus1RTRFProgramPresentEnable, fmnPlus1TARFPresentEnable, fmnPlus1TAFaultEnable, fmnPlus1TAWarningEnable, fmnPlus1TBRFPresentEnable, 
				fmnPlus1TBFaultEnable, fmnPlus1TBWarningEnable, fmnPlus1RedundancySwitchOverPriority, fmnPlus1LocalModePriority, fmnPlus1ControlUnitFaultPriority, 
				fmnPlus1SwitchOverModePriority, fmnPlus1SwitchOverReadyPriority, fmnPlus1SwitchOverExecutedPriority, fmnPlus1SwitchOverFaultPriority, fmnPlus1ChannelSelectionPriority, 
				fmnPlus1MTRFProgramPresentPriority, fmnPlus1RTOpModePriority, fmnPlus1RTRFProgramPresentPriority, fmnPlus1TARFPresentPriority, fmnPlus1TAFaultPriority, 
				fmnPlus1TAWarningPriority, fmnPlus1TBRFPresentPriority, fmnPlus1TBFaultPriority, fmnPlus1TBWarningPriority, fmnPlus1TALocalMode, 
				fmnPlus1TBLocalMode, fmnPlus1TALocalModeEnable, fmnPlus1TBLocalModeEnable, fmnPlus1TALocalModePriority, fmnPlus1TBLocalModePriority, 
				fmnPlus1MTOpModePriority, fmnPlus1MTOpModeEnable, fmnPlus1MTOpMode }
			STATUS current
			DESCRIPTION 
				"Description.fm N+1 reserve: object group "
			::= { groupsnPlus1 1 }

		
		-- 1.3.6.1.4.1.19831.1.1.3.5.8.2
		eventGroupnPlus1 NOTIFICATION-GROUP
			NOTIFICATIONS { fmnPlus1RedundancySwitchOverEvent, fmnPlus1LocalModeEvent, fmnPlus1ControlUnitFaultEvent, fmnPlus1SwitchOverModeEvent, fmnPlus1SwitchOverReadyEvent, 
				fmnPlus1SwitchOverExecutedEvent, fmnPlus1SwitchOverFaultEvent, fmnPlus1ChannelSelectionEvent, fmnPlus1MTRFProgramPresentEvent, fmnPlus1RTOpModeEvent, 
				fmnPlus1RTRFProgramPresentEvent, fmnPlus1TARFPresentEvent, fmnPlus1TAFaultEvent, fmnPlus1TAWarningEvent, fmnPlus1TBRFPresentEvent, 
				fmnPlus1TBFaultEvent, fmnPlus1TBWarningEvent, fmnPlus1TALocalModeEvent, fmnPlus1TBLocalModeEvent, fmnPlus1MTOpModeEvent
				 }
			STATUS current
			DESCRIPTION 
				"Description.fm N+1 reserve: event group "
			::= { groupsnPlus1 2 }

		
		-- 1.3.6.1.4.1.19831.1.1.3.5.8.3
		objectGroupnPlus1obsolete OBJECT-GROUP
			OBJECTS { fmnPlus1TransmitterBReset, fmnPlus1TransmitterBMode, fmnPlus1TransmitterBResetEnable, fmnPlus1TransmitterBModeEnable, fmnPlus1TransmitterBResetPriority, 
				fmnPlus1TransmitterBModePriority }
			STATUS obsolete
			DESCRIPTION 
				"Description."
			::= { groupsnPlus1 3 }

		
		-- 1.3.6.1.4.1.19831.1.1.3.5.8.4
		eventGroupnPlus1obsolete NOTIFICATION-GROUP
			NOTIFICATIONS { fmnPlus1TransmitterBResetEvent, fmnPlus1TransmitterBModeEvent }
			STATUS obsolete
			DESCRIPTION 
				"Description."
			::= { groupsnPlus1 4 }

		
		-- 1.3.6.1.4.1.19831.1.1.3.5.9
		compliancenPlus1 OBJECT IDENTIFIER ::= { fmnPlus1 9 }

		
		-- 1.3.6.1.4.1.19831.1.1.3.5.9.1
		fmnPlus1Compliance MODULE-COMPLIANCE
			STATUS current
			DESCRIPTION 
				"Compliance Statement"
			MODULE -- this module
				MANDATORY-GROUPS { objectGroupnPlus1, eventGroupnPlus1 }
			::= { compliancenPlus1 1 }

		
	
	END

--
-- IRT-FM-NPLUS1-MIB.my
--
