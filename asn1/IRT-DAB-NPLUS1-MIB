--
-- IRT-DAB-NPLUS1-MIB.my
-- MIB generated by MG-SOFT Visual MIB Builder Version 6.0  Build 88
-- Wednesday, May 23, 2007 at 19:26:28
--

	IRT-DAB-NPLUS1-MIB DEFINITIONS ::= BEGIN
 
		IMPORTS
			eventTimeStamp, eventPriority, eventCounter, mibRelease			
				FROM IRT-COMMONVARBINDS-MIB			
			dab, LocalRemote, FaultOK, SelectManualAuto, ReadyNotReady, 
			ExecutedNotExecuted, Input1Input2, SelectOnOff, PresentNotPresent, OkNotOk, 
			WarningOK, MuteOk, SFNMFN			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DisplayString, TruthValue, TEXTUAL-CONVENTION			
				FROM SNMPv2-TC;
	
	
		-- 1.3.6.1.4.1.19831.1.1.2.5
		dabnPlus1 MODULE-IDENTITY 
			LAST-UPDATED "200705041400Z"		-- May 04, 2007 at 14:00 GMT
			ORGANIZATION 
				"IRT for WORKING-GROUP-TC-MIB"
			CONTACT-INFO 
				"Contact-info.
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				branch definition
				
				1st level
				
				events                         OBJECT IDENTIFIER ::= { dabnPlus1 0 }
				dabnPlus1General               OBJECT IDENTIFIER ::= { dabnPlus1 1 }
				  dabnPlus1MainTransmitterTable   is defined below as dabnPlus1 2
				dabnPlus1ReserveTransmitter    OBJECT IDENTIFIER ::= { dabnPlus1 3 }
				  dabnPlus1TransmitterATable      is defined below as dabnPlus1 4
				dabnPlus1TransmitterB          OBJECT IDENTIFIER ::= { dabnPlus1 5 }
				dabnPlus1EventEnable           OBJECT IDENTIFIER ::= { dabnPlus1 6 }
				dabnPlus1EventPriority         OBJECT IDENTIFIER ::= { dabnPlus1 7 }
				groups                         OBJECT IDENTIFIER ::= { dabnPlus1 8 }
				
				
				2nd level
				
				dabnPlus1EventEnableGeneral                OBJECT IDENTIFIER ::= { dabnPlus1EventEnable 1 }
				  dabnPlus1EventEnableMainTransmitterTable    is defined below as dabnPlus1EventEnable 2
				dabnPlus1EventEnableReserveTransmitter     OBJECT IDENTIFIER ::= { dabnPlus1EventEnable 3 }
				  dabnPlus1EventEnableTransmitterATable       is defined below as dabnPlus1EventEnable 4 }
				dabnPlus1EventEnableTransmitterB           OBJECT IDENTIFIER ::= { dabnPlus1EventEnable 5 }
				
				dabnPlus1EventPriorityGeneral              OBJECT IDENTIFIER ::= { dabnPlus1EventPriority 1 }
				  dabnPlus1EventPriorityMainTransmitterTable  is defined below as dabnPlus1EventPriority 2
				dabnPlus1EventPriorityReserveTransmitter   OBJECT IDENTIFIER ::= { dabnPlus1EventPriority 3 }
				  dabnPlus1EventPriorityTransmitterATable     is defined below as dabnPlus1EventPriority 4
				dabnPlus1EventPriorityTransmitterB         OBJECT IDENTIFIER ::= { dabnPlus1EventPriority 5 }
				
				end branch"
			REVISION "200705041400Z"		-- May 04, 2007 at 14:00 GMT
			DESCRIPTION 
				"change SFNMode, LocalMode (description) and Module-COMPLIANCE
				change numbering: OIDs
				1.3.6.1.4.1.19831.1.1.2.5.3.x and
				1.3.6.1.4.1.19831.1.1.2.5.5.x and
				1.3.6.1.4.1.19831.1.1.2.5.6.3.x and
				1.3.6.1.4.1.19831.1.1.2.5.6.5.x and
				1.3.6.1.4.1.19831.1.1.2.5.7.3.x and
				1.3.6.1.4.1.19831.1.1.2.5.7.5.2"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dab 5 }

		
	
--
-- Textual conventions
--
	
		TransmitterBFreeOccupied ::= TEXTUAL-CONVENTION
			STATUS obsolete
			DESCRIPTION 
				"Convention is inactive!
				
				Description. Free/Occupied message for transmitter B
				
				(1) free              
				(2) occupied          "
			SYNTAX INTEGER
				{
				free(1),
				occupied(2)
				}

	
--
-- Node definitions
--
	
-- dab N+1 Reserve. Events
		-- 1.3.6.1.4.1.19831.1.1.2.5.0
		dabEventsnPlus1 OBJECT IDENTIFIER ::= { dabnPlus1 0 }

		
		-- 1.3.6.1.4.1.19831.1.1.2.5.0.1
		dabnPlus1ResetFaultEvent NOTIFICATION-TYPE
			OBJECTS { sysDescr, sysName, sysLocation, eventTimeStamp, eventPriority, 
				eventCounter, dabnPlus1ResetFault }
			STATUS obsolete
			DESCRIPTION 
				"Notification is inactive!
				
				Description. dabnPlus1ResetFault notification"
			::= { dabEventsnPlus1 1 }

		
		-- 1.3.6.1.4.1.19831.1.1.2.5.0.2
		dabnPlus1RedundancySwitchOverEvent NOTIFICATION-TYPE
			OBJECTS { sysDescr, sysName, sysLocation, eventTimeStamp, eventPriority, 
				eventCounter, dabnPlus1RedundancySwitchOver }
			STATUS current
			DESCRIPTION 
				"Description. dabnPlus1RedundancySwitchOver notification"
			::= { dabEventsnPlus1 2 }

		
		-- 1.3.6.1.4.1.19831.1.1.2.5.0.3
		dabnPlus1LocalModeEvent NOTIFICATION-TYPE
			OBJECTS { sysDescr, sysName, sysLocation, eventTimeStamp, eventPriority, 
				eventCounter, dabnPlus1LocalMode }
			STATUS current
			DESCRIPTION 
				"Description. dabnPlus1LocalMode notification"
			::= { dabEventsnPlus1 3 }

		
		-- 1.3.6.1.4.1.19831.1.1.2.5.0.4
		dabnPlus1ControlUnitFaultEvent NOTIFICATION-TYPE
			OBJECTS { sysDescr, sysName, sysLocation, eventTimeStamp, eventPriority, 
				eventCounter, dabnPlus1ControlUnitFault }
			STATUS current
			DESCRIPTION 
				"Description. dabnPlus1ControlUnitFault notification"
			::= { dabEventsnPlus1 4 }

		
		-- 1.3.6.1.4.1.19831.1.1.2.5.0.5
		dabnPlus1SwitchOverModeEvent NOTIFICATION-TYPE
			OBJECTS { sysDescr, sysName, sysLocation, eventTimeStamp, eventPriority, 
				eventCounter, dabnPlus1SwitchOverMode }
			STATUS current
			DESCRIPTION 
				"Description. dabnPlus1SwitchOverMode notification"
			::= { dabEventsnPlus1 5 }

		
		-- 1.3.6.1.4.1.19831.1.1.2.5.0.6
		dabnPlus1SwitchOverReadyEvent NOTIFICATION-TYPE
			OBJECTS { sysDescr, sysName, sysLocation, eventTimeStamp, eventPriority, 
				eventCounter, dabnPlus1SwitchOverReady }
			STATUS current
			DESCRIPTION 
				"Description. dabnPlus1SwitchOverReady notification"
			::= { dabEventsnPlus1 6 }

		
		-- 1.3.6.1.4.1.19831.1.1.2.5.0.7
		dabnPlus1SwitchOverExecutedEvent NOTIFICATION-TYPE
			OBJECTS { sysDescr, sysName, sysLocation, eventTimeStamp, eventPriority, 
				eventCounter, dabnPlus1SwitchOverExecuted }
			STATUS current
			DESCRIPTION 
				"Description. dabnPlus1SwitchOverExecuted notification"
			::= { dabEventsnPlus1 7 }

		
		-- 1.3.6.1.4.1.19831.1.1.2.5.0.8
		dabnPlus1SwitchOverFaultEvent NOTIFICATION-TYPE
			OBJECTS { sysDescr, sysName, sysLocation, eventTimeStamp, eventPriority, 
				eventCounter, dabnPlus1SwitchOverFault }
			STATUS current
			DESCRIPTION 
				"Description. dabnPlus1SwitchOverFault notification"
			::= { dabEventsnPlus1 8 }

		
		-- 1.3.6.1.4.1.19831.1.1.2.5.0.9
		dabnPlus1ChannelSelectionEvent NOTIFICATION-TYPE
			OBJECTS { sysDescr, sysName, sysLocation, eventTimeStamp, eventPriority, 
				eventCounter, dabnPlus1ChannelSelection }
			STATUS current
			DESCRIPTION 
				"Description. dabnPlus1ChannelSelection notification"
			::= { dabEventsnPlus1 9 }

		
		-- 1.3.6.1.4.1.19831.1.1.2.5.0.10
		dabnPlus1TransmitterBResetEvent NOTIFICATION-TYPE
			OBJECTS { sysDescr, sysName, sysLocation, eventTimeStamp, eventPriority, 
				eventCounter, dabnPlus1TransmitterBReset }
			STATUS obsolete
			DESCRIPTION 
				"Notification is inactive!
				
				Description. dabnPlus1TransmitterBReset notification"
			::= { dabEventsnPlus1 10 }

		
		-- 1.3.6.1.4.1.19831.1.1.2.5.0.11
		dabnPlus1TransmitterBModeEvent NOTIFICATION-TYPE
			OBJECTS { sysDescr, sysName, sysLocation, eventTimeStamp, eventPriority, 
				eventCounter, dabnPlus1TransmitterBMode }
			STATUS obsolete
			DESCRIPTION 
				"Notification is inactive!
				
				Description. dabnPlus1TransmitterBMode notification"
			::= { dabEventsnPlus1 11 }

		
		-- 1.3.6.1.4.1.19831.1.1.2.5.0.12
		dabnPlus1MTInputPreselectionEvent NOTIFICATION-TYPE
			OBJECTS { sysDescr, sysName, sysLocation, eventTimeStamp, eventPriority, 
				eventCounter, dabnPlus1MTInputPreselection, dabnPlus1EventTransmitterIndex }
			STATUS current
			DESCRIPTION 
				"Description. dabnPlus1MTInputPreselection notification"
			::= { dabEventsnPlus1 12 }

		
		-- 1.3.6.1.4.1.19831.1.1.2.5.0.13
		dabnPlus1MTInputAutomaticEvent NOTIFICATION-TYPE
			OBJECTS { sysDescr, sysName, sysLocation, eventTimeStamp, eventPriority, 
				eventCounter, dabnPlus1MTInputAutomatic, dabnPlus1EventTransmitterIndex }
			STATUS current
			DESCRIPTION 
				"Description. dabnPlus1MTInputAutomatic notification"
			::= { dabEventsnPlus1 13 }

		
		-- 1.3.6.1.4.1.19831.1.1.2.5.0.14
		dabnPlus1MTOpModeEvent NOTIFICATION-TYPE
			OBJECTS { sysDescr, sysName, sysLocation, eventTimeStamp, eventPriority, 
				eventCounter, dabnPlus1MTOpMode, dabnPlus1EventTransmitterIndex }
			STATUS current
			DESCRIPTION 
				"Description. dabnPlus1MTOpMode notification"
			::= { dabEventsnPlus1 14 }

		
		-- 1.3.6.1.4.1.19831.1.1.2.5.0.15
		dabnPlus1MTRFProgramPresentEvent NOTIFICATION-TYPE
			OBJECTS { sysDescr, sysName, sysLocation, eventTimeStamp, eventPriority, 
				eventCounter, dabnPlus1MTRFProgramPresent, dabnPlus1EventTransmitterIndex }
			STATUS current
			DESCRIPTION 
				"Description. dabnPlus1MTRFProgramPresent notification"
			::= { dabEventsnPlus1 15 }

		
		-- 1.3.6.1.4.1.19831.1.1.2.5.0.16
		dabnPlus1RTInputPreselectionEvent NOTIFICATION-TYPE
			OBJECTS { sysDescr, sysName, sysLocation, eventTimeStamp, eventPriority, 
				eventCounter, dabnPlus1RTInputPreselection }
			STATUS current
			DESCRIPTION 
				"Description. dabnPlus1RTInputPreselection notification"
			::= { dabEventsnPlus1 16 }

		
		-- 1.3.6.1.4.1.19831.1.1.2.5.0.17
		dabnPlus1RTInputAutomaticEvent NOTIFICATION-TYPE
			OBJECTS { sysDescr, sysName, sysLocation, eventTimeStamp, eventPriority, 
				eventCounter, dabnPlus1RTInputAutomatic }
			STATUS current
			DESCRIPTION 
				"Description. dabnPlus1RTInputAutomatic notification"
			::= { dabEventsnPlus1 17 }

		
		-- 1.3.6.1.4.1.19831.1.1.2.5.0.18
		dabnPlus1RTOpModeEvent NOTIFICATION-TYPE
			OBJECTS { sysDescr, sysName, sysLocation, eventTimeStamp, eventPriority, 
				eventCounter, dabnPlus1RTOpMode }
			STATUS current
			DESCRIPTION 
				"Description. dabnPlus1RTOpMode notification"
			::= { dabEventsnPlus1 18 }

		
		-- 1.3.6.1.4.1.19831.1.1.2.5.0.19
		dabnPlus1RTRFProgramPresentEvent NOTIFICATION-TYPE
			OBJECTS { sysDescr, sysName, sysLocation, eventTimeStamp, eventPriority, 
				eventCounter, dabnPlus1RTRFProgramPresent }
			STATUS current
			DESCRIPTION 
				"Description. dabnPlus1RTRFProgramPresent notification"
			::= { dabEventsnPlus1 19 }

		
		-- 1.3.6.1.4.1.19831.1.1.2.5.0.20
		dabnPlus1TARFPresentEvent NOTIFICATION-TYPE
			OBJECTS { sysDescr, sysName, sysLocation, eventTimeStamp, eventPriority, 
				eventCounter, dabnPlus1TARFPresent, dabnPlus1EventTransmitterIndex }
			STATUS current
			DESCRIPTION 
				"Description. dabnPlus1TARFPresent notification"
			::= { dabEventsnPlus1 20 }

		
		-- 1.3.6.1.4.1.19831.1.1.2.5.0.21
		dabnPlus1TAInput1OKEvent NOTIFICATION-TYPE
			OBJECTS { sysDescr, sysName, sysLocation, eventTimeStamp, eventPriority, 
				eventCounter, dabnPlus1TAInput1OK, dabnPlus1EventTransmitterIndex }
			STATUS current
			DESCRIPTION 
				"Description. dabnPlus1TAInput1OK notification"
			::= { dabEventsnPlus1 21 }

		
		-- 1.3.6.1.4.1.19831.1.1.2.5.0.22
		dabnPlus1TAInput2OKEvent NOTIFICATION-TYPE
			OBJECTS { sysDescr, sysName, sysLocation, eventTimeStamp, eventPriority, 
				eventCounter, dabnPlus1TAInput2OK, dabnPlus1EventTransmitterIndex }
			STATUS current
			DESCRIPTION 
				"Description. dabnPlus1TAInput2OK notification"
			::= { dabEventsnPlus1 22 }

		
		-- 1.3.6.1.4.1.19831.1.1.2.5.0.23
		dabnPlus1TALocalModeEvent NOTIFICATION-TYPE
			OBJECTS { sysDescr, sysName, sysLocation, eventTimeStamp, eventPriority, 
				eventCounter, dabnPlus1TALocalMode, dabnPlus1EventTransmitterIndex }
			STATUS current
			DESCRIPTION 
				"Description. dabnPlus1TALocalMode notification"
			::= { dabEventsnPlus1 23 }

		
		-- 1.3.6.1.4.1.19831.1.1.2.5.0.24
		dabnPlus1TAInputPreselectionEvent NOTIFICATION-TYPE
			OBJECTS { sysDescr, sysName, sysLocation, eventTimeStamp, eventPriority, 
				eventCounter, dabnPlus1TAInputPreselection, dabnPlus1EventTransmitterIndex }
			STATUS current
			DESCRIPTION 
				"Description. dabnPlus1TAInputPreselection notification"
			::= { dabEventsnPlus1 24 }

		
		-- 1.3.6.1.4.1.19831.1.1.2.5.0.25
		dabnPlus1TAInputAutomaticEvent NOTIFICATION-TYPE
			OBJECTS { sysDescr, sysName, sysLocation, eventTimeStamp, eventPriority, 
				eventCounter, dabnPlus1TAInputAutomatic, dabnPlus1EventTransmitterIndex }
			STATUS current
			DESCRIPTION 
				"Description. dabnPlus1TAInputAutomatic notification"
			::= { dabEventsnPlus1 25 }

		
		-- 1.3.6.1.4.1.19831.1.1.2.5.0.26
		dabnPlus1TAFaultEvent NOTIFICATION-TYPE
			OBJECTS { sysDescr, sysName, sysLocation, eventTimeStamp, eventPriority, 
				eventCounter, dabnPlus1TAFault, dabnPlus1EventTransmitterIndex }
			STATUS current
			DESCRIPTION 
				"Description. dabnPlus1TAFault notification"
			::= { dabEventsnPlus1 26 }

		
		-- 1.3.6.1.4.1.19831.1.1.2.5.0.27
		dabnPlus1TAWarningEvent NOTIFICATION-TYPE
			OBJECTS { sysDescr, sysName, sysLocation, eventTimeStamp, eventPriority, 
				eventCounter, dabnPlus1TAWarning, dabnPlus1EventTransmitterIndex }
			STATUS current
			DESCRIPTION 
				"Description. dabnPlus1TAWarning notification"
			::= { dabEventsnPlus1 27 }

		
		-- 1.3.6.1.4.1.19831.1.1.2.5.0.28
		dabnPlus1TAActiveInputEvent NOTIFICATION-TYPE
			OBJECTS { sysDescr, sysName, sysLocation, eventTimeStamp, eventPriority, 
				eventCounter, dabnPlus1TAActiveInput, dabnPlus1EventTransmitterIndex }
			STATUS current
			DESCRIPTION 
				"Description. dabnPlus1TAActiveInput notification"
			::= { dabEventsnPlus1 28 }

		
		-- 1.3.6.1.4.1.19831.1.1.2.5.0.29
		dabnPlus1TASFNModeEvent NOTIFICATION-TYPE
			OBJECTS { sysDescr, sysName, sysLocation, eventTimeStamp, eventPriority, 
				eventCounter, dabnPlus1TASFNMode, dabnPlus1EventTransmitterIndex }
			STATUS current
			DESCRIPTION 
				"Description. dabnPlus1TASFNMode notification"
			::= { dabEventsnPlus1 29 }

		
		-- 1.3.6.1.4.1.19831.1.1.2.5.0.30
		dabnPlus1TARefFaultEvent NOTIFICATION-TYPE
			OBJECTS { sysDescr, sysName, sysLocation, eventTimeStamp, eventPriority, 
				eventCounter, dabnPlus1TARefFault, dabnPlus1EventTransmitterIndex }
			STATUS current
			DESCRIPTION 
				"Description. dabnPlus1TARefFault notification"
			::= { dabEventsnPlus1 30 }

		
		-- 1.3.6.1.4.1.19831.1.1.2.5.0.31
		dabnPlus1TAMuteEvent NOTIFICATION-TYPE
			OBJECTS { sysDescr, sysName, sysLocation, eventTimeStamp, eventPriority, 
				eventCounter, dabnPlus1TAMute, dabnPlus1EventTransmitterIndex }
			STATUS current
			DESCRIPTION 
				"Description. dabnPlus1TAMute notification"
			::= { dabEventsnPlus1 31 }

		
		-- 1.3.6.1.4.1.19831.1.1.2.5.0.32
		dabnPlus1TAWarningTimeStampEvent NOTIFICATION-TYPE
			OBJECTS { sysDescr, sysName, sysLocation, eventTimeStamp, eventPriority, 
				eventCounter, dabnPlus1TAWarningTimeStamp, dabnPlus1EventTransmitterIndex }
			STATUS current
			DESCRIPTION 
				"Description. dabnPlus1TAWarningTimeStamp notification"
			::= { dabEventsnPlus1 32 }

		
		-- 1.3.6.1.4.1.19831.1.1.2.5.0.33
		dabnPlus1TBRFPresentEvent NOTIFICATION-TYPE
			OBJECTS { sysDescr, sysName, sysLocation, eventTimeStamp, eventPriority, 
				eventCounter, dabnPlus1TBRFPresent }
			STATUS current
			DESCRIPTION 
				"Description. dabnPlus1TBRFPresent notification"
			::= { dabEventsnPlus1 33 }

		
		-- 1.3.6.1.4.1.19831.1.1.2.5.0.34
		dabnPlus1TBInput1OKEvent NOTIFICATION-TYPE
			OBJECTS { sysDescr, sysName, sysLocation, eventTimeStamp, eventPriority, 
				eventCounter, dabnPlus1TBInput1OK }
			STATUS current
			DESCRIPTION 
				"Description. dabnPlus1TBInput1OK notification"
			::= { dabEventsnPlus1 34 }

		
		-- 1.3.6.1.4.1.19831.1.1.2.5.0.35
		dabnPlus1TBInput2OKEvent NOTIFICATION-TYPE
			OBJECTS { sysDescr, sysName, sysLocation, eventTimeStamp, eventPriority, 
				eventCounter, dabnPlus1TBInput2OK }
			STATUS current
			DESCRIPTION 
				"Description. dabnPlus1TBInput2OK notification"
			::= { dabEventsnPlus1 35 }

		
		-- 1.3.6.1.4.1.19831.1.1.2.5.0.36
		dabnPlus1TBLocalModeEvent NOTIFICATION-TYPE
			OBJECTS { sysDescr, sysName, sysLocation, eventTimeStamp, eventPriority, 
				eventCounter, dabnPlus1TBLocalMode }
			STATUS current
			DESCRIPTION 
				"Description. dabnPlus1TBLocalMode notification"
			::= { dabEventsnPlus1 36 }

		
		-- 1.3.6.1.4.1.19831.1.1.2.5.0.37
		dabnPlus1TBFaultEvent NOTIFICATION-TYPE
			OBJECTS { sysDescr, sysName, sysLocation, eventTimeStamp, eventPriority, 
				eventCounter, dabnPlus1TBFault }
			STATUS current
			DESCRIPTION 
				"Description. dabnPlus1TBFault notification"
			::= { dabEventsnPlus1 37 }

		
		-- 1.3.6.1.4.1.19831.1.1.2.5.0.38
		dabnPlus1TBWarningEvent NOTIFICATION-TYPE
			OBJECTS { sysDescr, sysName, sysLocation, eventTimeStamp, eventPriority, 
				eventCounter, dabnPlus1TBWarning }
			STATUS current
			DESCRIPTION 
				"Description. dabnPlus1TBWarning notification"
			::= { dabEventsnPlus1 38 }

		
		-- 1.3.6.1.4.1.19831.1.1.2.5.0.39
		dabnPlus1TBInputPreselectionEvent NOTIFICATION-TYPE
			OBJECTS { sysDescr, sysName, sysLocation, eventTimeStamp, eventPriority, 
				eventCounter, dabnPlus1TBInputPreselection }
			STATUS current
			DESCRIPTION 
				"Description. dabnPlus1TBInputPreselection notification"
			::= { dabEventsnPlus1 39 }

		
		-- 1.3.6.1.4.1.19831.1.1.2.5.0.40
		dabnPlus1TBInputAutomaticEvent NOTIFICATION-TYPE
			OBJECTS { sysDescr, sysName, sysLocation, eventTimeStamp, eventPriority, 
				eventCounter, dabnPlus1TBInputAutomatic }
			STATUS current
			DESCRIPTION 
				"Description. dabnPlus1TBInputAutomatic notification"
			::= { dabEventsnPlus1 40 }

		
		-- 1.3.6.1.4.1.19831.1.1.2.5.0.41
		dabnPlus1TBActiveInputEvent NOTIFICATION-TYPE
			OBJECTS { sysDescr, sysName, sysLocation, eventTimeStamp, eventPriority, 
				eventCounter, dabnPlus1TBActiveInput }
			STATUS current
			DESCRIPTION 
				"Description. dabnPlus1TBActiveInput notification"
			::= { dabEventsnPlus1 41 }

		
		-- 1.3.6.1.4.1.19831.1.1.2.5.0.42
		dabnPlus1TBSFNModeEvent NOTIFICATION-TYPE
			OBJECTS { sysDescr, sysName, sysLocation, eventTimeStamp, eventPriority, 
				eventCounter, dabnPlus1TBSFNMode }
			STATUS current
			DESCRIPTION 
				"Description. dabnPlus1TBSFNMode notification"
			::= { dabEventsnPlus1 42 }

		
		-- 1.3.6.1.4.1.19831.1.1.2.5.0.43
		dabnPlus1TBRefFaultEvent NOTIFICATION-TYPE
			OBJECTS { sysDescr, sysName, sysLocation, eventTimeStamp, eventPriority, 
				eventCounter, dabnPlus1TBRefFault }
			STATUS current
			DESCRIPTION 
				"Description. dabnPlus1TBRefFault notification"
			::= { dabEventsnPlus1 43 }

		
		-- 1.3.6.1.4.1.19831.1.1.2.5.0.44
		dabnPlus1TBMuteEvent NOTIFICATION-TYPE
			OBJECTS { sysDescr, sysName, sysLocation, eventTimeStamp, eventPriority, 
				eventCounter, dabnPlus1TBMute }
			STATUS current
			DESCRIPTION 
				"Description. dabnPlus1TBMute notification"
			::= { dabEventsnPlus1 44 }

		
		-- 1.3.6.1.4.1.19831.1.1.2.5.0.45
		dabnPlus1TBWarningTimeStampEvent NOTIFICATION-TYPE
			OBJECTS { sysDescr, sysName, sysLocation, eventTimeStamp, eventPriority, 
				eventCounter, dabnPlus1TBWarningTimeStamp }
			STATUS current
			DESCRIPTION 
				"Description. dabnPlus1TBWarningTimeStamp notification"
			::= { dabEventsnPlus1 45 }

		
-- dab N+1 Resreve. General
		-- 1.3.6.1.4.1.19831.1.1.2.5.1
		dabnPlus1General OBJECT IDENTIFIER ::= { dabnPlus1 1 }

		
		-- 1.3.6.1.4.1.19831.1.1.2.5.1.1
		dabnPlus1ResetFault OBJECT-TYPE
			SYNTAX Unsigned32
			MAX-ACCESS read-write
			STATUS obsolete
			DESCRIPTION
				"Massage is inactive!
				
				N+1 reserve. Reset fault: Trigger for reset the sum fault
				
				<1>
				
				(1) reset sum fault
				"
			::= { dabnPlus1General 1 }

		
		-- 1.3.6.1.4.1.19831.1.1.2.5.1.2
		dabnPlus1RedundancySwitchOver OBJECT-TYPE
			SYNTAX INTEGER (-1..6)
			MAX-ACCESS read-write
			STATUS current
			DESCRIPTION
				"N+1 reserve. Redundancy reserve switch over for transmitters B,A1,A2...An
				
				<-1,0,1,2,3,4,...,n>
				
				(-1) reserve transmitterB
				(0) undefined
				(1) transmitter 1
				(2) transmitter 2
				(3) transmitter 3
				(4) transmitter 4
				................
				(n) transmitter n
				"
			::= { dabnPlus1General 2 }

		
		-- 1.3.6.1.4.1.19831.1.1.2.5.1.3
		dabnPlus1LocalMode OBJECT-TYPE
			SYNTAX LocalRemote
			MAX-ACCESS read-only
			STATUS current
			DESCRIPTION
				"N+1 reserve. Local mode
				
				(0) undefined
				(1) local
				(2) remote"
			::= { dabnPlus1General 3 }

		
		-- 1.3.6.1.4.1.19831.1.1.2.5.1.4
		dabnPlus1ControlUnitFault OBJECT-TYPE
			SYNTAX FaultOK
			MAX-ACCESS read-only
			STATUS current
			DESCRIPTION
				"N+1 reserve. State of the control unit
				
				(0) undefined
				(1) fault
				(2) ok"
			::= { dabnPlus1General 4 }

		
		-- 1.3.6.1.4.1.19831.1.1.2.5.1.5
		dabnPlus1SwitchOverMode OBJECT-TYPE
			SYNTAX SelectManualAuto
			MAX-ACCESS read-write
			STATUS current
			DESCRIPTION
				"N+1 reserve. Switch over mode: manual or automatic
				
				(0) undefined
				(1) manual 
				(2) automatic"
			::= { dabnPlus1General 5 }

		
		-- 1.3.6.1.4.1.19831.1.1.2.5.1.6
		dabnPlus1SwitchOverReady OBJECT-TYPE
			SYNTAX ReadyNotReady
			MAX-ACCESS read-only
			STATUS current
			DESCRIPTION
				"State of the N+1 reserve  switch over unit
				
				(0) undefined
				(1) ready
				(2) not ready"
			::= { dabnPlus1General 6 }

		
		-- 1.3.6.1.4.1.19831.1.1.2.5.1.7
		dabnPlus1SwitchOverExecuted OBJECT-TYPE
			SYNTAX ExecutedNotExecuted
			MAX-ACCESS read-only
			STATUS current
			DESCRIPTION
				"N+1 reserve. Shows if the reserve switsch over uinit it has executed
				
				(0) undefined
				(1) executed
				(2) not executed"
			::= { dabnPlus1General 7 }

		
		-- 1.3.6.1.4.1.19831.1.1.2.5.1.8
		dabnPlus1SwitchOverFault OBJECT-TYPE
			SYNTAX FaultOK
			MAX-ACCESS read-only
			STATUS current
			DESCRIPTION
				"N+1 reserve. Fault state of the switch over unit
				
				(0) undefined
				(1) faulty
				(2) ok"
			::= { dabnPlus1General 8 }

		
		-- 1.3.6.1.4.1.19831.1.1.2.5.1.9
		dabnPlus1ChannelSelection OBJECT-TYPE
			SYNTAX Unsigned32
			MAX-ACCESS read-write
			STATUS current
			DESCRIPTION
				"N+1 reserve. Chanel selection 1...n of reserve transmitter
				
				<1,0,2,...,n>
				
				(0) undefined
				(1) chanel 1
				(2) chanel 2
				...
				(n) chanel n
				
				"
			::= { dabnPlus1General 9 }

		
		-- 1.3.6.1.4.1.19831.1.1.2.5.1.10
		dabnPlus1TransmitterBReset OBJECT-TYPE
			SYNTAX Unsigned32
			MAX-ACCESS read-write
			STATUS obsolete
			DESCRIPTION
				"Message is inactive!
				
				N+1 Reserve. Transmitter B reset: trigger for reset 
				
				<1>
				
				(1) reset fault
				"
			::= { dabnPlus1General 10 }

		
		-- 1.3.6.1.4.1.19831.1.1.2.5.1.11
		dabnPlus1TransmitterBMode OBJECT-TYPE
			SYNTAX TransmitterBFreeOccupied
			MAX-ACCESS read-only
			STATUS obsolete
			DESCRIPTION
				"Message is inactive!
				
				N+1 reserve. Transmitter B redundancy state
				
				(1) free
				(2) occupied
				"
			::= { dabnPlus1General 11 }

		
		-- 1.3.6.1.4.1.19831.1.1.2.5.1.12
		dabnPlus1EventTransmitterIndex OBJECT-TYPE
			SYNTAX Unsigned32 (1..255)
			MAX-ACCESS read-only
			STATUS current
			DESCRIPTION
				"N+1 reserve. Eventindex to be transmitted along which each trap from MaintransmitterTable or TransmitterATable"
			::= { dabnPlus1General 12 }

		
-- dab N+1 reserve. Main transmitter table
		-- 1.3.6.1.4.1.19831.1.1.2.5.2
		dabnPlus1MainTransmitterTable OBJECT-TYPE
			SYNTAX SEQUENCE OF DabnPlus1MainTransmitterEntry
			MAX-ACCESS not-accessible
			STATUS current
			DESCRIPTION
				"Table of logical transmitters carrying programs
				"
			::= { dabnPlus1 2 }

		
-- dab N+1 reserve: One logical transmitter, numbered from 1 to n
		-- 1.3.6.1.4.1.19831.1.1.2.5.2.1
		dabnPlus1MainTransmitterEntry OBJECT-TYPE
			SYNTAX DabnPlus1MainTransmitterEntry
			MAX-ACCESS not-accessible
			STATUS current
			DESCRIPTION
				"One logical transmitter, numbered from 1 to n"
			INDEX { dabnPlus1MTIndex }
			::= { dabnPlus1MainTransmitterTable 1 }

		
		DabnPlus1MainTransmitterEntry ::=
			SEQUENCE { 
				dabnPlus1MTIndex
					Unsigned32,
				dabnPlus1MTInputPreselection
					Input1Input2,
				dabnPlus1MTInputAutomatic
					SelectOnOff,
				dabnPlus1MTOpMode
					SelectOnOff,
				dabnPlus1MTRFProgramPresent
					PresentNotPresent
			 }

		-- 1.3.6.1.4.1.19831.1.1.2.5.2.1.1
		dabnPlus1MTIndex OBJECT-TYPE
			SYNTAX Unsigned32 (1..255)
			MAX-ACCESS read-only
			STATUS current
			DESCRIPTION
				"N+1 Reserve. Main transmitter index
				
				
				(1) transmitter 1
				(2) transmitter 2
				(3) transmitter 3
				(4) transmitter 4
				(5) transmitter 5
				(6) transmitter 6
				"
			::= { dabnPlus1MainTransmitterEntry 1 }

		
		-- 1.3.6.1.4.1.19831.1.1.2.5.2.1.2
		dabnPlus1MTInputPreselection OBJECT-TYPE
			SYNTAX Input1Input2
			MAX-ACCESS read-write
			STATUS current
			DESCRIPTION
				"Important! This message (logical view) is redundant with analogue massage 
				dabnPlus1TAInputPreselection OID: 1.3.6.1.4.1.19831.1.1.2.5.4.1.6
				below the node dabnPlus1TransmitterATable. 
				In the operation system mandatory there must be used only one of these views:
				
				 logical
				or
				 physical
				
				N+1 Reserve.Main transmitter preselection  input 
				
				(0) undefined
				(1) Input 1
				(2) Input 2"
			::= { dabnPlus1MainTransmitterEntry 2 }

		
		-- 1.3.6.1.4.1.19831.1.1.2.5.2.1.3
		dabnPlus1MTInputAutomatic OBJECT-TYPE
			SYNTAX SelectOnOff
			MAX-ACCESS read-write
			STATUS current
			DESCRIPTION
				"Important! This message (logical view) is redundant with analogue massage 
				dabnPlus1TAInputAutomatic OID: 1.3.6.1.4.1.19831.1.1.2.5.4.1.7
				below the node dabnPlus1TransmitterATable. 
				In the operation system mandatory there must be used only one of these views:
				
				 logical
				or
				 physical
				
				N+1 Reserve. Main transmitter reserve input
				
				(0) undefined
				(1) ON 
				(2) OFF "
			::= { dabnPlus1MainTransmitterEntry 3 }

		
		-- 1.3.6.1.4.1.19831.1.1.2.5.2.1.4
		dabnPlus1MTOpMode OBJECT-TYPE
			SYNTAX SelectOnOff
			MAX-ACCESS read-write
			STATUS current
			DESCRIPTION
				"N+1 Reserve. General transmitter control 
				
				(0) undefined
				(1) ON
				(2) OFF"
			::= { dabnPlus1MainTransmitterEntry 4 }

		
		-- 1.3.6.1.4.1.19831.1.1.2.5.2.1.5
		dabnPlus1MTRFProgramPresent OBJECT-TYPE
			SYNTAX PresentNotPresent
			MAX-ACCESS read-only
			STATUS current
			DESCRIPTION
				"N+1 reserve. Describes if the output power of the   main transmitter is present
				
				(0) undefined
				(1) present
				(2) not present"
			::= { dabnPlus1MainTransmitterEntry 5 }

		
-- dab N+1 reserve. Reserve Transmitter
		-- 1.3.6.1.4.1.19831.1.1.2.5.3
		dabnPlus1ReserveTransmitter OBJECT IDENTIFIER ::= { dabnPlus1 3 }

		
		-- 1.3.6.1.4.1.19831.1.1.2.5.3.2
		dabnPlus1RTInputPreselection OBJECT-TYPE
			SYNTAX Input1Input2
			MAX-ACCESS read-write
			STATUS current
			DESCRIPTION
				"Important! This message (logical view) is redundant with analogue massage 
				dabnPlus1TBInputPreselection OID: 1.3.6.1.4.1.19831.1.1.2.5.5.5
				below the node dabnPlus1Transmitter B. 
				In the operation system mandatory there must be used only one of these views:
				
				 logical
				or
				 physical
				
				N+1 reserve. Preselection input reserve transmitter  
				
				(0) undefined
				(1) Input 1
				(2) Input 2"
			::= { dabnPlus1ReserveTransmitter 2 }

		
		-- 1.3.6.1.4.1.19831.1.1.2.5.3.3
		dabnPlus1RTInputAutomatic OBJECT-TYPE
			SYNTAX SelectOnOff
			MAX-ACCESS read-write
			STATUS current
			DESCRIPTION
				"Important! This message (logical view) is redundant with analogue massage 
				dabnPlus1TBInputAutomatic OID: 1.3.6.1.4.1.19831.1.1.2.5.5.6
				below the node dabnPlus1TransmitterB. 
				In the operation system mandatory there must be used only one of these views:
				
				 logical
				or
				 physical
				
				
				
				N+1 reserve. Reserve transmitter control 
				
				(0) undefined
				(1) ON 
				(2) OFF "
			::= { dabnPlus1ReserveTransmitter 3 }

		
		-- 1.3.6.1.4.1.19831.1.1.2.5.3.4
		dabnPlus1RTOpMode OBJECT-TYPE
			SYNTAX SelectOnOff
			MAX-ACCESS read-write
			STATUS current
			DESCRIPTION
				"N+1 reserve. reserve transmitter control
				
				(0) undefined
				(1) ON
				(2) OFF"
			::= { dabnPlus1ReserveTransmitter 4 }

		
		-- 1.3.6.1.4.1.19831.1.1.2.5.3.5
		dabnPlus1RTRFProgramPresent OBJECT-TYPE
			SYNTAX PresentNotPresent
			MAX-ACCESS read-only
			STATUS current
			DESCRIPTION
				"N+1 reserve. Describes if the output power of the   reserve transmitter is present
				
				(0) undefined
				(1) present
				(2) not present"
			::= { dabnPlus1ReserveTransmitter 5 }

		
-- dab N+1 reserve. Transmitter A table
		-- 1.3.6.1.4.1.19831.1.1.2.5.4
		dabnPlus1TransmitterATable OBJECT-TYPE
			SYNTAX SEQUENCE OF DabnPlus1TransmitterAEntry
			MAX-ACCESS not-accessible
			STATUS current
			DESCRIPTION
				"Table of physical transmitters ment to be on air in normal operation"
			::= { dabnPlus1 4 }

		
-- dab n+1 reserve: transmitter A entry - rows
		-- 1.3.6.1.4.1.19831.1.1.2.5.4.1
		dabnPlus1TransmitterAEntry OBJECT-TYPE
			SYNTAX DabnPlus1TransmitterAEntry
			MAX-ACCESS not-accessible
			STATUS current
			DESCRIPTION
				"N+1 reserve. One physical transmitter, numbered from A1 to An"
			INDEX { dabnPlus1TAIndex }
			::= { dabnPlus1TransmitterATable 1 }

		
		DabnPlus1TransmitterAEntry ::=
			SEQUENCE { 
				dabnPlus1TAIndex
					Unsigned32,
				dabnPlus1TARFPresent
					PresentNotPresent,
				dabnPlus1TAInput1OK
					OkNotOk,
				dabnPlus1TAInput2OK
					OkNotOk,
				dabnPlus1TALocalMode
					LocalRemote,
				dabnPlus1TAInputPreselection
					Input1Input2,
				dabnPlus1TAInputAutomatic
					SelectManualAuto,
				dabnPlus1TAFault
					FaultOK,
				dabnPlus1TAWarning
					WarningOK,
				dabnPlus1TAActiveInput
					INTEGER,
				dabnPlus1TASFNMode
					SFNMFN,
				dabnPlus1TARefFault
					FaultOK,
				dabnPlus1TAMute
					MuteOk,
				dabnPlus1TAWarningTimeStamp
					WarningOK
			 }

		-- 1.3.6.1.4.1.19831.1.1.2.5.4.1.1
		dabnPlus1TAIndex OBJECT-TYPE
			SYNTAX Unsigned32 (1..255)
			MAX-ACCESS read-only
			STATUS current
			DESCRIPTION
				"N+1 reserve. Index of the  transmitters A1,A2...An
				
				"
			::= { dabnPlus1TransmitterAEntry 1 }

		
		-- 1.3.6.1.4.1.19831.1.1.2.5.4.1.2
		dabnPlus1TARFPresent OBJECT-TYPE
			SYNTAX PresentNotPresent
			MAX-ACCESS read-only
			STATUS current
			DESCRIPTION
				"N+1 reserve. Describes if the output power of the  transmitter A is present
				
				(0) undefined
				(1) present
				(2) not present"
			::= { dabnPlus1TransmitterAEntry 2 }

		
		-- 1.3.6.1.4.1.19831.1.1.2.5.4.1.3
		dabnPlus1TAInput1OK OBJECT-TYPE
			SYNTAX OkNotOk
			MAX-ACCESS read-only
			STATUS current
			DESCRIPTION
				"N+1 reserve. Describes if the input signal at the input 1 of  transmitter A is ok
				
				(0) undefined
				(1) signal ok
				(2) signal is not ok "
			::= { dabnPlus1TransmitterAEntry 3 }

		
		-- 1.3.6.1.4.1.19831.1.1.2.5.4.1.4
		dabnPlus1TAInput2OK OBJECT-TYPE
			SYNTAX OkNotOk
			MAX-ACCESS read-only
			STATUS current
			DESCRIPTION
				"N+1 reserve. Describes if the input signal at the input 2 of  transmitter A is ok
				
				(0) undefined
				(1) signal ok
				(2) signal is not ok "
			::= { dabnPlus1TransmitterAEntry 4 }

		
		-- 1.3.6.1.4.1.19831.1.1.2.5.4.1.5
		dabnPlus1TALocalMode OBJECT-TYPE
			SYNTAX LocalRemote
			MAX-ACCESS read-only
			STATUS current
			DESCRIPTION
				"N+1 reserve. Local mode of the  transmitter A
				
				(0) undefined
				(1) local
				(2) remote"
			::= { dabnPlus1TransmitterAEntry 5 }

		
		-- 1.3.6.1.4.1.19831.1.1.2.5.4.1.6
		dabnPlus1TAInputPreselection OBJECT-TYPE
			SYNTAX Input1Input2
			MAX-ACCESS read-write
			STATUS current
			DESCRIPTION
				"
				Important! This message (logical view) is redundant with analogue massage 
				dabnPlus1MTInputPreselection OID: 1.3.6.1.4.1.19831.1.1.2.5.2.1.2
				below the node dabnPlus1MainTransmitterTable. 
				In the operation system mandatory there must be used only one of these views:
				
				 logical
				or
				 physical
				
				N+1 reserve. Preselection input of transmitter A
				
				(0) undefined
				(1) Input 1
				(2) Input 2"
			::= { dabnPlus1TransmitterAEntry 6 }

		
		-- 1.3.6.1.4.1.19831.1.1.2.5.4.1.7
		dabnPlus1TAInputAutomatic OBJECT-TYPE
			SYNTAX SelectManualAuto
			MAX-ACCESS read-write
			STATUS current
			DESCRIPTION
				"Important! This message (logical view) is redundant with analogue massage 
				dabnPlus1MTInputAutomatic OID: 1.3.6.1.4.1.19831.1.1.2.5.2.1.3
				below the node dabnPlus1MainTransmitterTable. 
				In the operation system mandatory there must be used only one of these views:
				
				 logical
				or
				 physical
				
				N+1 reserve. Input selection mode of the transmitter A:  manual or automatic
				
				(0) undefined
				(1) manual 
				(2) automatic"
			::= { dabnPlus1TransmitterAEntry 7 }

		
		-- 1.3.6.1.4.1.19831.1.1.2.5.4.1.8
		dabnPlus1TAFault OBJECT-TYPE
			SYNTAX FaultOK
			MAX-ACCESS read-only
			STATUS current
			DESCRIPTION
				"N+1 reserve. Fault state of the transmitter A
				
				(0) undefined
				(1) fault
				(2) ok"
			::= { dabnPlus1TransmitterAEntry 8 }

		
		-- 1.3.6.1.4.1.19831.1.1.2.5.4.1.9
		dabnPlus1TAWarning OBJECT-TYPE
			SYNTAX WarningOK
			MAX-ACCESS read-only
			STATUS current
			DESCRIPTION
				"N+1 reserve. Warning state of transmiter A
				
				(0) undefined
				(1) warning
				(2) ok"
			::= { dabnPlus1TransmitterAEntry 9 }

		
		-- 1.3.6.1.4.1.19831.1.1.2.5.4.1.10
		dabnPlus1TAActiveInput OBJECT-TYPE
			SYNTAX INTEGER
				{
				undefined(0),
				input1(1),
				input2(2),
				seamless(3),
				hmHierarchicalModulation(4)
				}
			MAX-ACCESS read-only
			STATUS current
			DESCRIPTION
				"N+1 reserve. Active input of the transmitter A  
				
				"
			::= { dabnPlus1TransmitterAEntry 10 }

		
		-- 1.3.6.1.4.1.19831.1.1.2.5.4.1.11
		dabnPlus1TASFNMode OBJECT-TYPE
			SYNTAX SFNMFN
			MAX-ACCESS read-only
			STATUS current
			DESCRIPTION
				"N+1 reserve. SFN mode of transmitter A
				
				(0) undefined
				(1) SFN
				(2) MFN"
			::= { dabnPlus1TransmitterAEntry 11 }

		
		-- 1.3.6.1.4.1.19831.1.1.2.5.4.1.12
		dabnPlus1TARefFault OBJECT-TYPE
			SYNTAX FaultOK
			MAX-ACCESS read-only
			STATUS current
			DESCRIPTION
				"N+1 reserve. FAult state of the GPS input or reference frequency of transmitter A
				
				(0) undefined
				(1) fault
				(2) ok"
			::= { dabnPlus1TransmitterAEntry 12 }

		
		-- 1.3.6.1.4.1.19831.1.1.2.5.4.1.13
		dabnPlus1TAMute OBJECT-TYPE
			SYNTAX MuteOk
			MAX-ACCESS read-only
			STATUS current
			DESCRIPTION
				"N+1 reserve. Mute state of transmitter A
				
				(0) undefined
				(1) mute
				(2) ok"
			::= { dabnPlus1TransmitterAEntry 13 }

		
		-- 1.3.6.1.4.1.19831.1.1.2.5.4.1.14
		dabnPlus1TAWarningTimeStamp OBJECT-TYPE
			SYNTAX WarningOK
			MAX-ACCESS read-only
			STATUS current
			DESCRIPTION
				"N+1 reserve. Time stamp warning state of transmiter A
				
				(0) undefined
				(1) warning
				(2) ok"
			::= { dabnPlus1TransmitterAEntry 14 }

		
-- dab N+1. Transmitter B
		-- 1.3.6.1.4.1.19831.1.1.2.5.5
		dabnPlus1TransmitterB OBJECT IDENTIFIER ::= { dabnPlus1 5 }

		
		-- 1.3.6.1.4.1.19831.1.1.2.5.5.2
		dabnPlus1TBRFPresent OBJECT-TYPE
			SYNTAX PresentNotPresent
			MAX-ACCESS read-only
			STATUS current
			DESCRIPTION
				"n+1 reserve:  Describes if the output power of the  transmitter B is present
				
				(0) undefined
				(1) present
				(2) not present"
			::= { dabnPlus1TransmitterB 2 }

		
		-- 1.3.6.1.4.1.19831.1.1.2.5.5.3
		dabnPlus1TBInput1OK OBJECT-TYPE
			SYNTAX OkNotOk
			MAX-ACCESS read-only
			STATUS current
			DESCRIPTION
				"N+1 reserve. Describes if the input signal at the input 1 of reserve is ok
				
				(0) undefined
				(1) signal ok
				(2) signal is not ok "
			::= { dabnPlus1TransmitterB 3 }

		
		-- 1.3.6.1.4.1.19831.1.1.2.5.5.4
		dabnPlus1TBInput2OK OBJECT-TYPE
			SYNTAX OkNotOk
			MAX-ACCESS read-only
			STATUS current
			DESCRIPTION
				"N+1 reserve. Describes if the input signal at the input 2 of reserve is ok
				
				(0) undefined
				(1) signal ok
				(2) signal is not ok "
			::= { dabnPlus1TransmitterB 4 }

		
		-- 1.3.6.1.4.1.19831.1.1.2.5.5.5
		dabnPlus1TBLocalMode OBJECT-TYPE
			SYNTAX LocalRemote
			MAX-ACCESS read-only
			STATUS current
			DESCRIPTION
				"N+1 reserve. Reserve local mode: Describes the output Power of the  transmitter B
				
				(0) undefined
				(1) local
				(2) remote"
			::= { dabnPlus1TransmitterB 5 }

		
		-- 1.3.6.1.4.1.19831.1.1.2.5.5.6
		dabnPlus1TBInputPreselection OBJECT-TYPE
			SYNTAX Input1Input2
			MAX-ACCESS read-write
			STATUS current
			DESCRIPTION
				"Important! This message (logical view) is redundant with analogue massage 
				dabnPlus1RTInputPreselectionReserve OID: 1.3.6.1.4.1.19831.1.1.2.5.3.1
				below the node dabnPlus1ReserveTransmitter. 
				In the operation system mandatory there must be used only one of these views:
				
				 logical
				or
				 physical
				
				N+1 reserve. Preselection input reserve transmitter  
				
				(0) undefined
				(1) Input 1
				(2) Input 2
				
				
				"
			::= { dabnPlus1TransmitterB 6 }

		
		-- 1.3.6.1.4.1.19831.1.1.2.5.5.7
		dabnPlus1TBInputAutomatic OBJECT-TYPE
			SYNTAX SelectManualAuto
			MAX-ACCESS read-write
			STATUS current
			DESCRIPTION
				"Important! This message (logical view) is redundant with analogue massage 
				dabnPlus1RTInputAutomaticReserve OID: 1.3.6.1.4.1.19831.1.1.2.5.3.2
				below the node dabnPlus1TransmitterB. 
				In the operation system mandatory there must be used only one of these views:
				
				 logical
				or
				 physical
				
				
				N+1 reserve. Reserve input selection mode: manual or automatic
				
				(0) undefined
				(1) manual 
				(2) automatic"
			::= { dabnPlus1TransmitterB 7 }

		
		-- 1.3.6.1.4.1.19831.1.1.2.5.5.8
		dabnPlus1TBFault OBJECT-TYPE
			SYNTAX FaultOK
			MAX-ACCESS read-only
			STATUS current
			DESCRIPTION
				"N+1 reserve. Fault state of reserve 
				
				(0) undefined
				(1) fault
				(2) ok"
			::= { dabnPlus1TransmitterB 8 }

		
		-- 1.3.6.1.4.1.19831.1.1.2.5.5.9
		dabnPlus1TBWarning OBJECT-TYPE
			SYNTAX WarningOK
			MAX-ACCESS read-only
			STATUS current
			DESCRIPTION
				"n+1 reserve. Warning state of reserve
				
				(0) undefined
				(1) warning
				(2) ok"
			::= { dabnPlus1TransmitterB 9 }

		
		-- 1.3.6.1.4.1.19831.1.1.2.5.5.10
		dabnPlus1TBActiveInput OBJECT-TYPE
			SYNTAX INTEGER
				{
				undefined(0),
				input1(1),
				input2(2),
				seamless(3),
				hmHierarchicalModulation(4)
				}
			MAX-ACCESS read-only
			STATUS current
			DESCRIPTION
				"N+1 reserve. Active input of the reserve
				
				"
			::= { dabnPlus1TransmitterB 10 }

		
		-- 1.3.6.1.4.1.19831.1.1.2.5.5.11
		dabnPlus1TBSFNMode OBJECT-TYPE
			SYNTAX SFNMFN
			MAX-ACCESS read-only
			STATUS current
			DESCRIPTION
				"N+1 reserve. SFN mode of reserve
				
				(0) undefined
				(1) SFN
				(2) MFN"
			::= { dabnPlus1TransmitterB 11 }

		
		-- 1.3.6.1.4.1.19831.1.1.2.5.5.12
		dabnPlus1TBRefFault OBJECT-TYPE
			SYNTAX FaultOK
			MAX-ACCESS read-only
			STATUS current
			DESCRIPTION
				"N+1 reserve. Fault state of the GPS input or the reference frequency of reserve transmitter
				
				(0) undefined
				(1) fault
				(2) ok"
			::= { dabnPlus1TransmitterB 12 }

		
		-- 1.3.6.1.4.1.19831.1.1.2.5.5.13
		dabnPlus1TBMute OBJECT-TYPE
			SYNTAX MuteOk
			MAX-ACCESS read-only
			STATUS current
			DESCRIPTION
				"N+1 reserve. Mute state of reserve
				
				(0) undefined
				(1) mute
				(2) ok"
			::= { dabnPlus1TransmitterB 13 }

		
		-- 1.3.6.1.4.1.19831.1.1.2.5.5.14
		dabnPlus1TBWarningTimeStamp OBJECT-TYPE
			SYNTAX WarningOK
			MAX-ACCESS read-only
			STATUS current
			DESCRIPTION
				"N+1 reserve. Time stamp warning state of transmiter B
				
				(0) undefined
				(1) warning
				(2) ok"
			::= { dabnPlus1TransmitterB 14 }

		
-- dab N+1 reserve. Switch for event 
		-- 1.3.6.1.4.1.19831.1.1.2.5.6
		dabnPlus1EventEnable OBJECT IDENTIFIER ::= { dabnPlus1 6 }

		
-- dab N+1 reserve. general:  events 
		-- 1.3.6.1.4.1.19831.1.1.2.5.6.1
		dabnPlus1EventEnableGeneral OBJECT IDENTIFIER ::= { dabnPlus1EventEnable 1 }

		
		-- 1.3.6.1.4.1.19831.1.1.2.5.6.1.1
		dabnPlus1ResetFaultEnable OBJECT-TYPE
			SYNTAX TruthValue
			MAX-ACCESS read-write
			STATUS obsolete
			DESCRIPTION
				"Massage is inactive!
				
				Description. Enable/Disable switch for dabnPlus1ResetFault event"
			::= { dabnPlus1EventEnableGeneral 1 }

		
		-- 1.3.6.1.4.1.19831.1.1.2.5.6.1.2
		dabnPlus1RedundancySwitchOverEnable OBJECT-TYPE
			SYNTAX TruthValue
			MAX-ACCESS read-write
			STATUS current
			DESCRIPTION
				"Description. Enable/Disable switch for dabnPlus1RedundancySwitchOve event"
			::= { dabnPlus1EventEnableGeneral 2 }

		
		-- 1.3.6.1.4.1.19831.1.1.2.5.6.1.3
		dabnPlus1LocalModeEnable OBJECT-TYPE
			SYNTAX TruthValue
			MAX-ACCESS read-write
			STATUS current
			DESCRIPTION
				"Description. Enable/Disable switch for dabnPlus1LocalMode event"
			::= { dabnPlus1EventEnableGeneral 3 }

		
		-- 1.3.6.1.4.1.19831.1.1.2.5.6.1.4
		dabnPlus1ControlUnitFaultEnable OBJECT-TYPE
			SYNTAX TruthValue
			MAX-ACCESS read-write
			STATUS current
			DESCRIPTION
				"Description. Enable/Disable switch for dabnPlus1ControlUnitFault event"
			::= { dabnPlus1EventEnableGeneral 4 }

		
		-- 1.3.6.1.4.1.19831.1.1.2.5.6.1.5
		dabnPlus1SwitchOverModeEnable OBJECT-TYPE
			SYNTAX TruthValue
			MAX-ACCESS read-write
			STATUS current
			DESCRIPTION
				"Description. Enable/Disable switch for dabnPlus1SwitchOverMode event"
			::= { dabnPlus1EventEnableGeneral 5 }

		
		-- 1.3.6.1.4.1.19831.1.1.2.5.6.1.6
		dabnPlus1SwitchOverReadyEnable OBJECT-TYPE
			SYNTAX TruthValue
			MAX-ACCESS read-write
			STATUS current
			DESCRIPTION
				"Description. Enable/Disable switch for dabnPlus1SwitchOverReady event"
			::= { dabnPlus1EventEnableGeneral 6 }

		
		-- 1.3.6.1.4.1.19831.1.1.2.5.6.1.7
		dabnPlus1SwitchOverExecutedEnable OBJECT-TYPE
			SYNTAX TruthValue
			MAX-ACCESS read-write
			STATUS current
			DESCRIPTION
				"Description. Enable/Disable switch for dabnPlus1SwitchOverExecuted event"
			::= { dabnPlus1EventEnableGeneral 7 }

		
		-- 1.3.6.1.4.1.19831.1.1.2.5.6.1.8
		dabnPlus1SwitchOverFaultEnable OBJECT-TYPE
			SYNTAX TruthValue
			MAX-ACCESS read-write
			STATUS current
			DESCRIPTION
				"Description. Enable/Disable switch for dabnPlus1SwitchOverFault event"
			::= { dabnPlus1EventEnableGeneral 8 }

		
		-- 1.3.6.1.4.1.19831.1.1.2.5.6.1.9
		dabnPlus1ChannelSelectionEnable OBJECT-TYPE
			SYNTAX TruthValue
			MAX-ACCESS read-write
			STATUS current
			DESCRIPTION
				"Description. Enable/Disable switch for dabnPlus1ChannelSelection event"
			::= { dabnPlus1EventEnableGeneral 9 }

		
		-- 1.3.6.1.4.1.19831.1.1.2.5.6.1.10
		dabnPlus1TransmitterBResetEnable OBJECT-TYPE
			SYNTAX TruthValue
			MAX-ACCESS read-write
			STATUS obsolete
			DESCRIPTION
				"Message is inactive!
				
				Description. Enable/Disable switch for dabnPlus1TransmitterBReset event"
			::= { dabnPlus1EventEnableGeneral 10 }

		
		-- 1.3.6.1.4.1.19831.1.1.2.5.6.1.11
		dabnPlus1TransmitterBModeEnable OBJECT-TYPE
			SYNTAX TruthValue
			MAX-ACCESS read-write
			STATUS obsolete
			DESCRIPTION
				"Message is inactive!
				
				Description. Enable/Disable switch for dabnPlus1TransmitterBMode event"
			::= { dabnPlus1EventEnableGeneral 11 }

		
-- dab N+1 reserve. main transmitter table: events 
		-- 1.3.6.1.4.1.19831.1.1.2.5.6.2
		dabnPlus1EventEnableMainTransmitterTable OBJECT-TYPE
			SYNTAX SEQUENCE OF DabnPlus1EventEnableMainTransmitterEntry
			MAX-ACCESS not-accessible
			STATUS current
			DESCRIPTION
				"dab N+1 reserve. Transmitters main transmitter table: switch for events 
				"
			::= { dabnPlus1EventEnable 2 }

		
-- dab N+1 reserve: Main transmitter table rows
		-- 1.3.6.1.4.1.19831.1.1.2.5.6.2.1
		dabnPlus1EventEnableMainTransmitterEntry OBJECT-TYPE
			SYNTAX DabnPlus1EventEnableMainTransmitterEntry
			MAX-ACCESS not-accessible
			STATUS current
			DESCRIPTION
				"One logical transmitter, numbered from 1 to n"
			INDEX { dabnPlus1MTIndex }
			::= { dabnPlus1EventEnableMainTransmitterTable 1 }

		
		DabnPlus1EventEnableMainTransmitterEntry ::=
			SEQUENCE { 
				dabnPlus1MTInputPreselectionEnable
					TruthValue,
				dabnPlus1MTInputAutomaticEnable
					TruthValue,
				dabnPlus1MTOpModeEnable
					TruthValue,
				dabnPlus1MTRFProgramPresentEnable
					TruthValue
			 }

		-- 1.3.6.1.4.1.19831.1.1.2.5.6.2.1.2
		dabnPlus1MTInputPreselectionEnable OBJECT-TYPE
			SYNTAX TruthValue
			MAX-ACCESS read-write
			STATUS current
			DESCRIPTION
				"Description. Enable/Disable switch for dabnPlus1MTInputPreselection event"
			::= { dabnPlus1EventEnableMainTransmitterEntry 2 }

		
		-- 1.3.6.1.4.1.19831.1.1.2.5.6.2.1.3
		dabnPlus1MTInputAutomaticEnable OBJECT-TYPE
			SYNTAX TruthValue
			MAX-ACCESS read-write
			STATUS current
			DESCRIPTION
				"Description. Enable/Disable switch for dabnPlus1MTInputAutomatic event"
			::= { dabnPlus1EventEnableMainTransmitterEntry 3 }

		
		-- 1.3.6.1.4.1.19831.1.1.2.5.6.2.1.4
		dabnPlus1MTOpModeEnable OBJECT-TYPE
			SYNTAX TruthValue
			MAX-ACCESS read-write
			STATUS current
			DESCRIPTION
				"Description. Enable/Disable switch for dabnPlus1MTOpMode event"
			::= { dabnPlus1EventEnableMainTransmitterEntry 4 }

		
		-- 1.3.6.1.4.1.19831.1.1.2.5.6.2.1.5
		dabnPlus1MTRFProgramPresentEnable OBJECT-TYPE
			SYNTAX TruthValue
			MAX-ACCESS read-write
			STATUS current
			DESCRIPTION
				"Description. Enable/Disable switch for dabnPlus1MTRFProgramPresent event"
			::= { dabnPlus1EventEnableMainTransmitterEntry 5 }

		
-- dab N+1 reserve. reserve transmitter: events
		-- 1.3.6.1.4.1.19831.1.1.2.5.6.3
		dabnPlus1EventEnableReserveTransmitter OBJECT IDENTIFIER ::= { dabnPlus1EventEnable 3 }

		
		-- 1.3.6.1.4.1.19831.1.1.2.5.6.3.2
		dabnPlus1RTInputPreselectionEnable OBJECT-TYPE
			SYNTAX TruthValue
			MAX-ACCESS read-write
			STATUS current
			DESCRIPTION
				"Description. Enable/Disable switch for dabnPlus1RTInputPreselection event"
			::= { dabnPlus1EventEnableReserveTransmitter 2 }

		
		-- 1.3.6.1.4.1.19831.1.1.2.5.6.3.3
		dabnPlus1RTInputAutomaticEnable OBJECT-TYPE
			SYNTAX TruthValue
			MAX-ACCESS read-write
			STATUS current
			DESCRIPTION
				"Description. Enable/Disable switch for dabnPlus1RTInputAutomatic event"
			::= { dabnPlus1EventEnableReserveTransmitter 3 }

		
		-- 1.3.6.1.4.1.19831.1.1.2.5.6.3.4
		dabnPlus1RTOpModeEnable OBJECT-TYPE
			SYNTAX TruthValue
			MAX-ACCESS read-write
			STATUS current
			DESCRIPTION
				"Description. Enable/Disable switch for dabnPlus1RTOpMode event"
			::= { dabnPlus1EventEnableReserveTransmitter 4 }

		
		-- 1.3.6.1.4.1.19831.1.1.2.5.6.3.5
		dabnPlus1RTRFProgramPresentEnable OBJECT-TYPE
			SYNTAX TruthValue
			MAX-ACCESS read-write
			STATUS current
			DESCRIPTION
				"Description. Enable/Disable switch for dabnPlus1RTRFProgramPresent event"
			::= { dabnPlus1EventEnableReserveTransmitter 5 }

		
-- N+1 reserve. Transmitters A table: events 
		-- 1.3.6.1.4.1.19831.1.1.2.5.6.4
		dabnPlus1EventEnableTransmitterATable OBJECT-TYPE
			SYNTAX SEQUENCE OF DabnPlus1EventEnableTransmitterAEntry
			MAX-ACCESS not-accessible
			STATUS current
			DESCRIPTION
				"N+1 reserve. Transmitters A table: switch for events "
			::= { dabnPlus1EventEnable 4 }

		
-- dab N+1 reserve: transmitter A entry - rows
		-- 1.3.6.1.4.1.19831.1.1.2.5.6.4.1
		dabnPlus1EventEnableTransmitterAEntry OBJECT-TYPE
			SYNTAX DabnPlus1EventEnableTransmitterAEntry
			MAX-ACCESS not-accessible
			STATUS current
			DESCRIPTION
				"One physical transmitter, numbered from A1 to An"
			INDEX { dabnPlus1TAIndex }
			::= { dabnPlus1EventEnableTransmitterATable 1 }

		
		DabnPlus1EventEnableTransmitterAEntry ::=
			SEQUENCE { 
				dabnPlus1TARFPresentEnable
					TruthValue,
				dabnPlus1TAInput1OKEnable
					TruthValue,
				dabnPlus1TAInput2OKEnable
					TruthValue,
				dabnPlus1TALocalModeEnable
					TruthValue,
				dabnPlus1TAInputPreselectionEnable
					TruthValue,
				dabnPlus1TAInputAutomaticEnable
					TruthValue,
				dabnPlus1TAFaultEnable
					TruthValue,
				dabnPlus1TAWarningEnable
					TruthValue,
				dabnPlus1TAActiveInputEnable
					TruthValue,
				dabnPlus1TASFNModeEnable
					TruthValue,
				dabnPlus1TARefFaultEnable
					TruthValue,
				dabnPlus1TAMuteEnable
					TruthValue,
				dabnPlus1TAWarningTimeStampEnable
					TruthValue
			 }

		-- 1.3.6.1.4.1.19831.1.1.2.5.6.4.1.2
		dabnPlus1TARFPresentEnable OBJECT-TYPE
			SYNTAX TruthValue
			MAX-ACCESS read-write
			STATUS current
			DESCRIPTION
				"Description. Enable/Disable switch for dabnPlus1TARFPresent event"
			::= { dabnPlus1EventEnableTransmitterAEntry 2 }

		
		-- 1.3.6.1.4.1.19831.1.1.2.5.6.4.1.3
		dabnPlus1TAInput1OKEnable OBJECT-TYPE
			SYNTAX TruthValue
			MAX-ACCESS read-write
			STATUS current
			DESCRIPTION
				"Description. Enable/Disable switch for dabnPlus1TAInput1OK event"
			::= { dabnPlus1EventEnableTransmitterAEntry 3 }

		
		-- 1.3.6.1.4.1.19831.1.1.2.5.6.4.1.4
		dabnPlus1TAInput2OKEnable OBJECT-TYPE
			SYNTAX TruthValue
			MAX-ACCESS read-write
			STATUS current
			DESCRIPTION
				"Description. Enable/Disable switch for dabnPlus1TAInput2OK event"
			::= { dabnPlus1EventEnableTransmitterAEntry 4 }

		
		-- 1.3.6.1.4.1.19831.1.1.2.5.6.4.1.5
		dabnPlus1TALocalModeEnable OBJECT-TYPE
			SYNTAX TruthValue
			MAX-ACCESS read-write
			STATUS current
			DESCRIPTION
				"Description. Enable/Disable switch for dabnPlus1TALocalMode event"
			::= { dabnPlus1EventEnableTransmitterAEntry 5 }

		
		-- 1.3.6.1.4.1.19831.1.1.2.5.6.4.1.6
		dabnPlus1TAInputPreselectionEnable OBJECT-TYPE
			SYNTAX TruthValue
			MAX-ACCESS read-write
			STATUS current
			DESCRIPTION
				"Description. Enable/Disable switch for dabnPlus1TAInputPreselection event"
			::= { dabnPlus1EventEnableTransmitterAEntry 6 }

		
		-- 1.3.6.1.4.1.19831.1.1.2.5.6.4.1.7
		dabnPlus1TAInputAutomaticEnable OBJECT-TYPE
			SYNTAX TruthValue
			MAX-ACCESS read-write
			STATUS current
			DESCRIPTION
				"Description. Enable/Disable switch for dabnPlus1TAInputAutomatic event"
			::= { dabnPlus1EventEnableTransmitterAEntry 7 }

		
		-- 1.3.6.1.4.1.19831.1.1.2.5.6.4.1.8
		dabnPlus1TAFaultEnable OBJECT-TYPE
			SYNTAX TruthValue
			MAX-ACCESS read-write
			STATUS current
			DESCRIPTION
				"Description. Enable/Disable switch for dabnPlus1TAFault event"
			::= { dabnPlus1EventEnableTransmitterAEntry 8 }

		
		-- 1.3.6.1.4.1.19831.1.1.2.5.6.4.1.9
		dabnPlus1TAWarningEnable OBJECT-TYPE
			SYNTAX TruthValue
			MAX-ACCESS read-write
			STATUS current
			DESCRIPTION
				"Description. Enable/Disable switch for dabnPlus1TAWarning event"
			::= { dabnPlus1EventEnableTransmitterAEntry 9 }

		
		-- 1.3.6.1.4.1.19831.1.1.2.5.6.4.1.10
		dabnPlus1TAActiveInputEnable OBJECT-TYPE
			SYNTAX TruthValue
			MAX-ACCESS read-write
			STATUS current
			DESCRIPTION
				"Description. Enable/Disable switch for dabnPlus1TAActiveInput event"
			::= { dabnPlus1EventEnableTransmitterAEntry 10 }

		
		-- 1.3.6.1.4.1.19831.1.1.2.5.6.4.1.11
		dabnPlus1TASFNModeEnable OBJECT-TYPE
			SYNTAX TruthValue
			MAX-ACCESS read-write
			STATUS current
			DESCRIPTION
				"Description. Enable/Disable switch for dabnPlus1TASFNMode event"
			::= { dabnPlus1EventEnableTransmitterAEntry 11 }

		
		-- 1.3.6.1.4.1.19831.1.1.2.5.6.4.1.12
		dabnPlus1TARefFaultEnable OBJECT-TYPE
			SYNTAX TruthValue
			MAX-ACCESS read-write
			STATUS current
			DESCRIPTION
				"Description. Enable/Disable switch for dabnPlus1TARefFault event"
			::= { dabnPlus1EventEnableTransmitterAEntry 12 }

		
		-- 1.3.6.1.4.1.19831.1.1.2.5.6.4.1.13
		dabnPlus1TAMuteEnable OBJECT-TYPE
			SYNTAX TruthValue
			MAX-ACCESS read-write
			STATUS current
			DESCRIPTION
				"Description. Enable/Disable switch for dabnPlus1TAMute event"
			::= { dabnPlus1EventEnableTransmitterAEntry 13 }

		
		-- 1.3.6.1.4.1.19831.1.1.2.5.6.4.1.14
		dabnPlus1TAWarningTimeStampEnable OBJECT-TYPE
			SYNTAX TruthValue
			MAX-ACCESS read-write
			STATUS current
			DESCRIPTION
				"Description. Enable/Disable switch for dabnPlus1TAWarningTimeStamp event"
			::= { dabnPlus1EventEnableTransmitterAEntry 14 }

		
-- dab N+1 transmitter B: events
		-- 1.3.6.1.4.1.19831.1.1.2.5.6.5
		dabnPlus1EventEnableTransmitterB OBJECT IDENTIFIER ::= { dabnPlus1EventEnable 5 }

		
		-- 1.3.6.1.4.1.19831.1.1.2.5.6.5.2
		dabnPlus1TBRFPresentEnable OBJECT-TYPE
			SYNTAX TruthValue
			MAX-ACCESS read-write
			STATUS current
			DESCRIPTION
				"Description. Enable/Disable switch for dabnPlus1TBRFPresent event"
			::= { dabnPlus1EventEnableTransmitterB 2 }

		
		-- 1.3.6.1.4.1.19831.1.1.2.5.6.5.3
		dabnPlus1TBInput1OKEnable OBJECT-TYPE
			SYNTAX TruthValue
			MAX-ACCESS read-write
			STATUS current
			DESCRIPTION
				"Description. Enable/Disable switch for dabnPlus1TBInput1OK event"
			::= { dabnPlus1EventEnableTransmitterB 3 }

		
		-- 1.3.6.1.4.1.19831.1.1.2.5.6.5.4
		dabnPlus1TBInput2OKEnable OBJECT-TYPE
			SYNTAX TruthValue
			MAX-ACCESS read-write
			STATUS current
			DESCRIPTION
				"Description. Enable/Disable switch for dabnPlus1TBInput2OK event"
			::= { dabnPlus1EventEnableTransmitterB 4 }

		
		-- 1.3.6.1.4.1.19831.1.1.2.5.6.5.5
		dabnPlus1TBLocalModeEnable OBJECT-TYPE
			SYNTAX TruthValue
			MAX-ACCESS read-write
			STATUS current
			DESCRIPTION
				"Description. Enable/Disable switch for dabnPlus1TBLocalMode event"
			::= { dabnPlus1EventEnableTransmitterB 5 }

		
		-- 1.3.6.1.4.1.19831.1.1.2.5.6.5.6
		dabnPlus1TBFaultEnable OBJECT-TYPE
			SYNTAX TruthValue
			MAX-ACCESS read-write
			STATUS current
			DESCRIPTION
				"Description. Enable/Disable switch for dabnPlus1TBFault event"
			::= { dabnPlus1EventEnableTransmitterB 6 }

		
		-- 1.3.6.1.4.1.19831.1.1.2.5.6.5.7
		dabnPlus1TBWarningEnable OBJECT-TYPE
			SYNTAX TruthValue
			MAX-ACCESS read-write
			STATUS current
			DESCRIPTION
				"Description. Enable/Disable switch for dabnPlus1TBWarning event"
			::= { dabnPlus1EventEnableTransmitterB 7 }

		
		-- 1.3.6.1.4.1.19831.1.1.2.5.6.5.8
		dabnPlus1TBInputPreselectionEnable OBJECT-TYPE
			SYNTAX TruthValue
			MAX-ACCESS read-write
			STATUS current
			DESCRIPTION
				"Description. Enable/Disable switch for dabnPlus1TBInputPreselection event"
			::= { dabnPlus1EventEnableTransmitterB 8 }

		
		-- 1.3.6.1.4.1.19831.1.1.2.5.6.5.9
		dabnPlus1TBInputAutomaticEnable OBJECT-TYPE
			SYNTAX TruthValue
			MAX-ACCESS read-write
			STATUS current
			DESCRIPTION
				"Description. Enable/Disable switch for dabnPlus1TBInputAutomatic event"
			::= { dabnPlus1EventEnableTransmitterB 9 }

		
		-- 1.3.6.1.4.1.19831.1.1.2.5.6.5.10
		dabnPlus1TBActiveInputEnable OBJECT-TYPE
			SYNTAX TruthValue
			MAX-ACCESS read-write
			STATUS current
			DESCRIPTION
				"Description. Enable/Disable switch for dabnPlus1TBActiveInput event"
			::= { dabnPlus1EventEnableTransmitterB 10 }

		
		-- 1.3.6.1.4.1.19831.1.1.2.5.6.5.11
		dabnPlus1TBSFNModeEnable OBJECT-TYPE
			SYNTAX TruthValue
			MAX-ACCESS read-write
			STATUS current
			DESCRIPTION
				"Description. Enable/Disable switch for dabnPlus1TBSFNMode event"
			::= { dabnPlus1EventEnableTransmitterB 11 }

		
		-- 1.3.6.1.4.1.19831.1.1.2.5.6.5.12
		dabnPlus1TBRefFaultEnable OBJECT-TYPE
			SYNTAX TruthValue
			MAX-ACCESS read-write
			STATUS current
			DESCRIPTION
				"Description. Enable/Disable switch for dabnPlus1TBRefFault event"
			::= { dabnPlus1EventEnableTransmitterB 12 }

		
		-- 1.3.6.1.4.1.19831.1.1.2.5.6.5.13
		dabnPlus1TBMuteEnable OBJECT-TYPE
			SYNTAX TruthValue
			MAX-ACCESS read-write
			STATUS current
			DESCRIPTION
				"Description. Enable/Disable switch for dabnPlus1TBMute event"
			::= { dabnPlus1EventEnableTransmitterB 13 }

		
		-- 1.3.6.1.4.1.19831.1.1.2.5.6.5.14
		dabnPlus1TBWarningTimeStampEnable OBJECT-TYPE
			SYNTAX TruthValue
			MAX-ACCESS read-write
			STATUS current
			DESCRIPTION
				"Description. Enable/Disable switch for dabnPlus1TBWarningTimeStamp event"
			::= { dabnPlus1EventEnableTransmitterB 14 }

		
-- dab N+1 reserve. Event priority
		-- 1.3.6.1.4.1.19831.1.1.2.5.7
		dabnPlus1EventPriority OBJECT IDENTIFIER ::= { dabnPlus1 7 }

		
-- dab n+1 reserve general: event priority
		-- 1.3.6.1.4.1.19831.1.1.2.5.7.1
		dabnPlus1EventPriorityGeneral OBJECT IDENTIFIER ::= { dabnPlus1EventPriority 1 }

		
		-- 1.3.6.1.4.1.19831.1.1.2.5.7.1.1
		dabnPlus1ResetFaultPriority OBJECT-TYPE
			SYNTAX Unsigned32
			MAX-ACCESS read-write
			STATUS obsolete
			DESCRIPTION
				"Massage is inactive!
				
				Description. Priority for dabnPlus1ResetFault event"
			::= { dabnPlus1EventPriorityGeneral 1 }

		
		-- 1.3.6.1.4.1.19831.1.1.2.5.7.1.2
		dabnPlus1RedundancySwitchOverPriority OBJECT-TYPE
			SYNTAX Unsigned32
			MAX-ACCESS read-write
			STATUS current
			DESCRIPTION
				"Priority switch for dabnPlus1RedundancySwitchOver event"
			::= { dabnPlus1EventPriorityGeneral 2 }

		
		-- 1.3.6.1.4.1.19831.1.1.2.5.7.1.3
		dabnPlus1LocalModePriority OBJECT-TYPE
			SYNTAX Unsigned32
			MAX-ACCESS read-write
			STATUS current
			DESCRIPTION
				"Priority switch for dabnPlus1LocalMode event"
			::= { dabnPlus1EventPriorityGeneral 3 }

		
		-- 1.3.6.1.4.1.19831.1.1.2.5.7.1.4
		dabnPlus1ControlUnitFaultPriority OBJECT-TYPE
			SYNTAX Unsigned32
			MAX-ACCESS read-write
			STATUS current
			DESCRIPTION
				"Priority switch for dabnPlus1ControlUnitFault event"
			::= { dabnPlus1EventPriorityGeneral 4 }

		
		-- 1.3.6.1.4.1.19831.1.1.2.5.7.1.5
		dabnPlus1SwitchOverModePriority OBJECT-TYPE
			SYNTAX Unsigned32
			MAX-ACCESS read-write
			STATUS current
			DESCRIPTION
				"Priority switch for dabnPlus1SwitchOverMode event"
			::= { dabnPlus1EventPriorityGeneral 5 }

		
		-- 1.3.6.1.4.1.19831.1.1.2.5.7.1.6
		dabnPlus1SwitchOverReadyPriority OBJECT-TYPE
			SYNTAX Unsigned32
			MAX-ACCESS read-write
			STATUS current
			DESCRIPTION
				"Priority switch for dabnPlus1SwitchOverReady event"
			::= { dabnPlus1EventPriorityGeneral 6 }

		
		-- 1.3.6.1.4.1.19831.1.1.2.5.7.1.7
		dabnPlus1SwitchOverExecutedPriority OBJECT-TYPE
			SYNTAX Unsigned32
			MAX-ACCESS read-write
			STATUS current
			DESCRIPTION
				"Priority switch for dabnPlus1SwitchOverExecuted event"
			::= { dabnPlus1EventPriorityGeneral 7 }

		
		-- 1.3.6.1.4.1.19831.1.1.2.5.7.1.8
		dabnPlus1SwitchOverFaultPriority OBJECT-TYPE
			SYNTAX Unsigned32
			MAX-ACCESS read-write
			STATUS current
			DESCRIPTION
				"Priority switch for dabnPlus1SwitchOverFault event"
			::= { dabnPlus1EventPriorityGeneral 8 }

		
		-- 1.3.6.1.4.1.19831.1.1.2.5.7.1.9
		dabnPlus1ChannelSelectionPriority OBJECT-TYPE
			SYNTAX Unsigned32
			MAX-ACCESS read-write
			STATUS current
			DESCRIPTION
				"Priority switch for dabnPlus1RChanelSelection event"
			::= { dabnPlus1EventPriorityGeneral 9 }

		
		-- 1.3.6.1.4.1.19831.1.1.2.5.7.1.10
		dabnPlus1TransmitterBResetPriority OBJECT-TYPE
			SYNTAX Unsigned32
			MAX-ACCESS read-write
			STATUS obsolete
			DESCRIPTION
				"Message is inactive!
				
				Priority switch for dabnPlus1TransmitterBReset event"
			::= { dabnPlus1EventPriorityGeneral 10 }

		
		-- 1.3.6.1.4.1.19831.1.1.2.5.7.1.11
		dabnPlus1TransmitterBModePriority OBJECT-TYPE
			SYNTAX Unsigned32
			MAX-ACCESS read-write
			STATUS obsolete
			DESCRIPTION
				"Message is inactive!
				
				Priority switch for dabnPlus1TransmitterBMode event"
			::= { dabnPlus1EventPriorityGeneral 11 }

		
-- dab N+1 reserve. Main transmitter table: event priority
		-- 1.3.6.1.4.1.19831.1.1.2.5.7.2
		dabnPlus1EventPriorityMainTransmitterTable OBJECT-TYPE
			SYNTAX SEQUENCE OF DabnPlus1EventPriorityMainTransmitterEntry
			MAX-ACCESS not-accessible
			STATUS current
			DESCRIPTION
				"dab n+1 reserve. general: priority for event"
			::= { dabnPlus1EventPriority 2 }

		
-- dvb N+1 reserve: Main transmitter table rows
		-- 1.3.6.1.4.1.19831.1.1.2.5.7.2.1
		dabnPlus1EventPriorityMainTransmitterEntry OBJECT-TYPE
			SYNTAX DabnPlus1EventPriorityMainTransmitterEntry
			MAX-ACCESS not-accessible
			STATUS current
			DESCRIPTION
				"One logical transmitter, numbered from 1 to n"
			INDEX { dabnPlus1MTIndex }
			::= { dabnPlus1EventPriorityMainTransmitterTable 1 }

		
		DabnPlus1EventPriorityMainTransmitterEntry ::=
			SEQUENCE { 
				dabnPlus1MTInputPreselectionPriority
					Unsigned32,
				dabnPlus1MTInputAutomaticPriority
					Unsigned32,
				dabnPlus1MTOpModePriority
					Unsigned32,
				dabnPlus1MTRFProgramPresentPriority
					Unsigned32
			 }

		-- 1.3.6.1.4.1.19831.1.1.2.5.7.2.1.2
		dabnPlus1MTInputPreselectionPriority OBJECT-TYPE
			SYNTAX Unsigned32
			MAX-ACCESS read-write
			STATUS current
			DESCRIPTION
				"Priority switch for dabnPlus1MTInputPreselection event"
			::= { dabnPlus1EventPriorityMainTransmitterEntry 2 }

		
		-- 1.3.6.1.4.1.19831.1.1.2.5.7.2.1.3
		dabnPlus1MTInputAutomaticPriority OBJECT-TYPE
			SYNTAX Unsigned32
			MAX-ACCESS read-write
			STATUS current
			DESCRIPTION
				"Priority switch for dabnPlus1MTInputAutomatic event"
			::= { dabnPlus1EventPriorityMainTransmitterEntry 3 }

		
		-- 1.3.6.1.4.1.19831.1.1.2.5.7.2.1.4
		dabnPlus1MTOpModePriority OBJECT-TYPE
			SYNTAX Unsigned32
			MAX-ACCESS read-write
			STATUS current
			DESCRIPTION
				"Priority switch for dabnPlus1MTOpMode event"
			::= { dabnPlus1EventPriorityMainTransmitterEntry 4 }

		
		-- 1.3.6.1.4.1.19831.1.1.2.5.7.2.1.5
		dabnPlus1MTRFProgramPresentPriority OBJECT-TYPE
			SYNTAX Unsigned32
			MAX-ACCESS read-write
			STATUS current
			DESCRIPTION
				"Priority switch for dabnPlus1MTRFProgramPresent event"
			::= { dabnPlus1EventPriorityMainTransmitterEntry 5 }

		
-- dab N+1 reserve. Reserve transmitter: event priority
		-- 1.3.6.1.4.1.19831.1.1.2.5.7.3
		dabnPlus1EventPriorityReserveTransmitter OBJECT IDENTIFIER ::= { dabnPlus1EventPriority 3 }

		
		-- 1.3.6.1.4.1.19831.1.1.2.5.7.3.2
		dabnPlus1RTInputPreselectionPriority OBJECT-TYPE
			SYNTAX Unsigned32
			MAX-ACCESS read-write
			STATUS current
			DESCRIPTION
				"Priority switch for dabnPlus1RTInputPreselection event"
			::= { dabnPlus1EventPriorityReserveTransmitter 2 }

		
		-- 1.3.6.1.4.1.19831.1.1.2.5.7.3.3
		dabnPlus1RTInputAutomaticPriority OBJECT-TYPE
			SYNTAX Unsigned32
			MAX-ACCESS read-write
			STATUS current
			DESCRIPTION
				"Priority switch for dabnPlus1RTInputAutomatic event"
			::= { dabnPlus1EventPriorityReserveTransmitter 3 }

		
		-- 1.3.6.1.4.1.19831.1.1.2.5.7.3.4
		dabnPlus1RTOpModePriority OBJECT-TYPE
			SYNTAX Unsigned32
			MAX-ACCESS read-write
			STATUS current
			DESCRIPTION
				"Priority switch for dabnPlus1RTOpMode event"
			::= { dabnPlus1EventPriorityReserveTransmitter 4 }

		
		-- 1.3.6.1.4.1.19831.1.1.2.5.7.3.5
		dabnPlus1RTRFProgramPresentPriority OBJECT-TYPE
			SYNTAX Unsigned32
			MAX-ACCESS read-write
			STATUS current
			DESCRIPTION
				"Priority switch for dabnPlus1RTRFProgramPresent event"
			::= { dabnPlus1EventPriorityReserveTransmitter 5 }

		
-- dab N+1 reserve. Transmitter A table: event priority
		-- 1.3.6.1.4.1.19831.1.1.2.5.7.4
		dabnPlus1EventPriorityTransmitterATable OBJECT-TYPE
			SYNTAX SEQUENCE OF DabnPlus1EventPriorityTransmitterAEntry
			MAX-ACCESS not-accessible
			STATUS current
			DESCRIPTION
				"dab n+1 reserve. transmitter A table: priority for event"
			::= { dabnPlus1EventPriority 4 }

		
-- dab N+1 reserve. Transmitter A entry - rows
		-- 1.3.6.1.4.1.19831.1.1.2.5.7.4.1
		dabnPlus1EventPriorityTransmitterAEntry OBJECT-TYPE
			SYNTAX DabnPlus1EventPriorityTransmitterAEntry
			MAX-ACCESS not-accessible
			STATUS current
			DESCRIPTION
				"One physical transmitter, numbered from A1 to An"
			INDEX { dabnPlus1TAIndex }
			::= { dabnPlus1EventPriorityTransmitterATable 1 }

		
		DabnPlus1EventPriorityTransmitterAEntry ::=
			SEQUENCE { 
				dabnPlus1TARFPresentPriority
					Unsigned32,
				dabnPlus1TAInput1OKPriority
					Unsigned32,
				dabnPlus1TAInput2OKPriority
					Unsigned32,
				dabnPlus1TALocalModePriority
					Unsigned32,
				dabnPlus1TAInputPreselectionPriority
					Unsigned32,
				dabnPlus1TAInputAutomaticPriority
					Unsigned32,
				dabnPlus1TAFaultPriority
					Unsigned32,
				dabnPlus1TAWarningPriority
					Unsigned32,
				dabnPlus1TAActiveInputPriority
					Unsigned32,
				dabnPlus1TASFNModePriority
					Unsigned32,
				dabnPlus1TARefFaultPriority
					Unsigned32,
				dabnPlus1TAMutePriority
					Unsigned32,
				dabnPlus1TAWarningTimeStampPriority
					Unsigned32
			 }

		-- 1.3.6.1.4.1.19831.1.1.2.5.7.4.1.2
		dabnPlus1TARFPresentPriority OBJECT-TYPE
			SYNTAX Unsigned32
			MAX-ACCESS read-write
			STATUS current
			DESCRIPTION
				"Priority switch for dabnPlus1TARFPresent event"
			::= { dabnPlus1EventPriorityTransmitterAEntry 2 }

		
		-- 1.3.6.1.4.1.19831.1.1.2.5.7.4.1.3
		dabnPlus1TAInput1OKPriority OBJECT-TYPE
			SYNTAX Unsigned32
			MAX-ACCESS read-write
			STATUS current
			DESCRIPTION
				"Priority switch for dabnPlus1TAInput1OK event"
			::= { dabnPlus1EventPriorityTransmitterAEntry 3 }

		
		-- 1.3.6.1.4.1.19831.1.1.2.5.7.4.1.4
		dabnPlus1TAInput2OKPriority OBJECT-TYPE
			SYNTAX Unsigned32
			MAX-ACCESS read-write
			STATUS current
			DESCRIPTION
				"Priority switch for dabnPlus1TAInput2OK event"
			::= { dabnPlus1EventPriorityTransmitterAEntry 4 }

		
		-- 1.3.6.1.4.1.19831.1.1.2.5.7.4.1.5
		dabnPlus1TALocalModePriority OBJECT-TYPE
			SYNTAX Unsigned32
			MAX-ACCESS read-write
			STATUS current
			DESCRIPTION
				"Priority switch for dabnPlus1TALocalModer event"
			::= { dabnPlus1EventPriorityTransmitterAEntry 5 }

		
		-- 1.3.6.1.4.1.19831.1.1.2.5.7.4.1.6
		dabnPlus1TAInputPreselectionPriority OBJECT-TYPE
			SYNTAX Unsigned32
			MAX-ACCESS read-write
			STATUS current
			DESCRIPTION
				"Priority switch for dabnPlus1TAInputPreselection event"
			::= { dabnPlus1EventPriorityTransmitterAEntry 6 }

		
		-- 1.3.6.1.4.1.19831.1.1.2.5.7.4.1.7
		dabnPlus1TAInputAutomaticPriority OBJECT-TYPE
			SYNTAX Unsigned32
			MAX-ACCESS read-write
			STATUS current
			DESCRIPTION
				"Priority switch for dabnPlus1TAInputAutomatic event"
			::= { dabnPlus1EventPriorityTransmitterAEntry 7 }

		
		-- 1.3.6.1.4.1.19831.1.1.2.5.7.4.1.8
		dabnPlus1TAFaultPriority OBJECT-TYPE
			SYNTAX Unsigned32
			MAX-ACCESS read-write
			STATUS current
			DESCRIPTION
				"Priority switch for dabnPlus1TAFaultPriority event"
			::= { dabnPlus1EventPriorityTransmitterAEntry 8 }

		
		-- 1.3.6.1.4.1.19831.1.1.2.5.7.4.1.9
		dabnPlus1TAWarningPriority OBJECT-TYPE
			SYNTAX Unsigned32
			MAX-ACCESS read-write
			STATUS current
			DESCRIPTION
				"Priority switch for dabnPlus1TAWarning event"
			::= { dabnPlus1EventPriorityTransmitterAEntry 9 }

		
		-- 1.3.6.1.4.1.19831.1.1.2.5.7.4.1.10
		dabnPlus1TAActiveInputPriority OBJECT-TYPE
			SYNTAX Unsigned32
			MAX-ACCESS read-write
			STATUS current
			DESCRIPTION
				"Priority switch for dabnPlus1TAActiveInput event"
			::= { dabnPlus1EventPriorityTransmitterAEntry 10 }

		
		-- 1.3.6.1.4.1.19831.1.1.2.5.7.4.1.11
		dabnPlus1TASFNModePriority OBJECT-TYPE
			SYNTAX Unsigned32
			MAX-ACCESS read-write
			STATUS current
			DESCRIPTION
				"Priority switch for dabnPlus1TASFNMode event"
			::= { dabnPlus1EventPriorityTransmitterAEntry 11 }

		
		-- 1.3.6.1.4.1.19831.1.1.2.5.7.4.1.12
		dabnPlus1TARefFaultPriority OBJECT-TYPE
			SYNTAX Unsigned32
			MAX-ACCESS read-write
			STATUS current
			DESCRIPTION
				"Priority switch for dabnPlus1TARefFault event"
			::= { dabnPlus1EventPriorityTransmitterAEntry 12 }

		
		-- 1.3.6.1.4.1.19831.1.1.2.5.7.4.1.13
		dabnPlus1TAMutePriority OBJECT-TYPE
			SYNTAX Unsigned32
			MAX-ACCESS read-write
			STATUS current
			DESCRIPTION
				"Priority switch for dabnPlus1TAMute event"
			::= { dabnPlus1EventPriorityTransmitterAEntry 13 }

		
		-- 1.3.6.1.4.1.19831.1.1.2.5.7.4.1.14
		dabnPlus1TAWarningTimeStampPriority OBJECT-TYPE
			SYNTAX Unsigned32
			MAX-ACCESS read-write
			STATUS current
			DESCRIPTION
				"Priority switch for dabnPlus1TAWarningTimeStamp event"
			::= { dabnPlus1EventPriorityTransmitterAEntry 14 }

		
-- dab N+1. transmitter B: event priority
		-- 1.3.6.1.4.1.19831.1.1.2.5.7.5
		dabnPlus1EventPriorityTransmitterB OBJECT IDENTIFIER ::= { dabnPlus1EventPriority 5 }

		
		-- 1.3.6.1.4.1.19831.1.1.2.5.7.5.2
		dabnPlus1TBRFPresentPriority OBJECT-TYPE
			SYNTAX Unsigned32
			MAX-ACCESS read-write
			STATUS current
			DESCRIPTION
				"Priority switch for dabnPlus1TBRFPresent event"
			::= { dabnPlus1EventPriorityTransmitterB 2 }

		
		-- 1.3.6.1.4.1.19831.1.1.2.5.7.5.3
		dabnPlus1TBInput1OKPriority OBJECT-TYPE
			SYNTAX Unsigned32
			MAX-ACCESS read-write
			STATUS current
			DESCRIPTION
				"Priority switch for dabnPlus1TBInput1OK event"
			::= { dabnPlus1EventPriorityTransmitterB 3 }

		
		-- 1.3.6.1.4.1.19831.1.1.2.5.7.5.4
		dabnPlus1TBInput2OKPriority OBJECT-TYPE
			SYNTAX Unsigned32
			MAX-ACCESS read-write
			STATUS current
			DESCRIPTION
				"Priority switch for dabnPlus1TBInput2OK event"
			::= { dabnPlus1EventPriorityTransmitterB 4 }

		
		-- 1.3.6.1.4.1.19831.1.1.2.5.7.5.5
		dabnPlus1TBLocalModePriority OBJECT-TYPE
			SYNTAX Unsigned32
			MAX-ACCESS read-write
			STATUS current
			DESCRIPTION
				"Priority switch for dabnPlus1TBLocalMode event"
			::= { dabnPlus1EventPriorityTransmitterB 5 }

		
		-- 1.3.6.1.4.1.19831.1.1.2.5.7.5.6
		dabnPlus1TBFaultPriority OBJECT-TYPE
			SYNTAX Unsigned32
			MAX-ACCESS read-write
			STATUS current
			DESCRIPTION
				"Priority switch for dabnPlus1TBFault event"
			::= { dabnPlus1EventPriorityTransmitterB 6 }

		
		-- 1.3.6.1.4.1.19831.1.1.2.5.7.5.7
		dabnPlus1TBWarningPriority OBJECT-TYPE
			SYNTAX Unsigned32
			MAX-ACCESS read-write
			STATUS current
			DESCRIPTION
				"Priority switch for dabnPlus1TBWarning event"
			::= { dabnPlus1EventPriorityTransmitterB 7 }

		
		-- 1.3.6.1.4.1.19831.1.1.2.5.7.5.8
		dabnPlus1TBInputPreselectionPriority OBJECT-TYPE
			SYNTAX Unsigned32
			MAX-ACCESS read-write
			STATUS current
			DESCRIPTION
				"Priority switch for dabnPlus1TBInputPreselection event"
			::= { dabnPlus1EventPriorityTransmitterB 8 }

		
		-- 1.3.6.1.4.1.19831.1.1.2.5.7.5.9
		dabnPlus1TBInputAutomaticPriority OBJECT-TYPE
			SYNTAX Unsigned32
			MAX-ACCESS read-write
			STATUS current
			DESCRIPTION
				"Priority switch for dabnPlus1TBInputAutomatic event"
			::= { dabnPlus1EventPriorityTransmitterB 9 }

		
		-- 1.3.6.1.4.1.19831.1.1.2.5.7.5.10
		dabnPlus1TBActiveInputPriority OBJECT-TYPE
			SYNTAX Unsigned32
			MAX-ACCESS read-write
			STATUS current
			DESCRIPTION
				"Priority switch for dabnPlus1TBActiveInput event"
			::= { dabnPlus1EventPriorityTransmitterB 10 }

		
		-- 1.3.6.1.4.1.19831.1.1.2.5.7.5.11
		dabnPlus1TBSFNModePriority OBJECT-TYPE
			SYNTAX Unsigned32
			MAX-ACCESS read-write
			STATUS current
			DESCRIPTION
				"NPriority switch for dabnPlus1TBSFNMode event"
			::= { dabnPlus1EventPriorityTransmitterB 11 }

		
		-- 1.3.6.1.4.1.19831.1.1.2.5.7.5.12
		dabnPlus1TBRefFaultPriority OBJECT-TYPE
			SYNTAX Unsigned32
			MAX-ACCESS read-write
			STATUS current
			DESCRIPTION
				"Priority switch for dabnPlus1TBRefFault event"
			::= { dabnPlus1EventPriorityTransmitterB 12 }

		
		-- 1.3.6.1.4.1.19831.1.1.2.5.7.5.13
		dabnPlus1TBMutePriority OBJECT-TYPE
			SYNTAX Unsigned32
			MAX-ACCESS read-write
			STATUS current
			DESCRIPTION
				"Priority switch for dabnPlus1TBMute event"
			::= { dabnPlus1EventPriorityTransmitterB 13 }

		
		-- 1.3.6.1.4.1.19831.1.1.2.5.7.5.14
		dabnPlus1TBWarningTimeStampPriority OBJECT-TYPE
			SYNTAX Unsigned32
			MAX-ACCESS read-write
			STATUS current
			DESCRIPTION
				"Priority switch for dabnPlus1TBWarningTimeStamp event"
			::= { dabnPlus1EventPriorityTransmitterB 14 }

		
		-- 1.3.6.1.4.1.19831.1.1.2.5.8
		groupsnPlus1 OBJECT IDENTIFIER ::= { dabnPlus1 8 }

		
		-- 1.3.6.1.4.1.19831.1.1.2.5.8.1
		objectGroupnPlus1 OBJECT-GROUP
			OBJECTS { dabnPlus1RedundancySwitchOver, dabnPlus1LocalMode, dabnPlus1ControlUnitFault, dabnPlus1SwitchOverMode, dabnPlus1SwitchOverReady, 
				dabnPlus1SwitchOverExecuted, dabnPlus1SwitchOverFault, dabnPlus1ChannelSelection, dabnPlus1EventTransmitterIndex, dabnPlus1MTIndex, 
				dabnPlus1MTInputPreselection, dabnPlus1MTInputAutomatic, dabnPlus1MTRFProgramPresent, dabnPlus1RTInputPreselection, dabnPlus1RTInputAutomatic, 
				dabnPlus1RTOpMode, dabnPlus1RTRFProgramPresent, dabnPlus1TAIndex, dabnPlus1TARFPresent, dabnPlus1TAInput1OK, 
				dabnPlus1TAInput2OK, dabnPlus1TALocalMode, dabnPlus1TAInputPreselection, dabnPlus1TAInputAutomatic, dabnPlus1TAFault, 
				dabnPlus1TAWarning, dabnPlus1TAActiveInput, dabnPlus1TASFNMode, dabnPlus1TARefFault, dabnPlus1TAMute, 
				dabnPlus1TAWarningTimeStamp, dabnPlus1TBRFPresent, dabnPlus1TBInput1OK, dabnPlus1TBInput2OK, dabnPlus1TBLocalMode, 
				dabnPlus1TBFault, dabnPlus1TBWarning, dabnPlus1TBInputPreselection, dabnPlus1TBInputAutomatic, dabnPlus1TBActiveInput, 
				dabnPlus1TBSFNMode, dabnPlus1TBRefFault, dabnPlus1TBMute, dabnPlus1TBWarningTimeStamp, dabnPlus1RedundancySwitchOverEnable, 
				dabnPlus1LocalModeEnable, dabnPlus1ControlUnitFaultEnable, dabnPlus1SwitchOverModeEnable, dabnPlus1SwitchOverReadyEnable, dabnPlus1SwitchOverExecutedEnable, 
				dabnPlus1SwitchOverFaultEnable, dabnPlus1ChannelSelectionEnable, dabnPlus1MTInputPreselectionEnable, dabnPlus1MTInputAutomaticEnable, dabnPlus1MTRFProgramPresentEnable, 
				dabnPlus1RTInputPreselectionEnable, dabnPlus1RTInputAutomaticEnable, dabnPlus1RTOpModeEnable, dabnPlus1RTRFProgramPresentEnable, dabnPlus1TARFPresentEnable, 
				dabnPlus1TAInput1OKEnable, dabnPlus1TAInput2OKEnable, dabnPlus1TALocalModeEnable, dabnPlus1TAInputPreselectionEnable, dabnPlus1TAInputAutomaticEnable, 
				dabnPlus1TAFaultEnable, dabnPlus1TAWarningEnable, dabnPlus1TAActiveInputEnable, dabnPlus1TASFNModeEnable, dabnPlus1TARefFaultEnable, 
				dabnPlus1TAMuteEnable, dabnPlus1TAWarningTimeStampEnable, dabnPlus1TBRFPresentEnable, dabnPlus1TBInput1OKEnable, dabnPlus1TBInput2OKEnable, 
				dabnPlus1TBLocalModeEnable, dabnPlus1TBFaultEnable, dabnPlus1TBWarningEnable, dabnPlus1TBInputPreselectionEnable, dabnPlus1TBInputAutomaticEnable, 
				dabnPlus1TBActiveInputEnable, dabnPlus1TBSFNModeEnable, dabnPlus1TBRefFaultEnable, dabnPlus1TBMuteEnable, dabnPlus1TBWarningTimeStampEnable, 
				dabnPlus1RedundancySwitchOverPriority, dabnPlus1LocalModePriority, dabnPlus1ControlUnitFaultPriority, dabnPlus1SwitchOverModePriority, dabnPlus1SwitchOverReadyPriority, 
				dabnPlus1SwitchOverExecutedPriority, dabnPlus1SwitchOverFaultPriority, dabnPlus1ChannelSelectionPriority, dabnPlus1MTInputPreselectionPriority, dabnPlus1MTInputAutomaticPriority, 
				dabnPlus1MTRFProgramPresentPriority, dabnPlus1RTInputPreselectionPriority, dabnPlus1RTInputAutomaticPriority, dabnPlus1RTOpModePriority, dabnPlus1RTRFProgramPresentPriority, 
				dabnPlus1TARFPresentPriority, dabnPlus1TAInput1OKPriority, dabnPlus1TAInput2OKPriority, dabnPlus1TALocalModePriority, dabnPlus1TAInputPreselectionPriority, 
				dabnPlus1TAInputAutomaticPriority, dabnPlus1TAFaultPriority, dabnPlus1TAWarningPriority, dabnPlus1TAActiveInputPriority, dabnPlus1TASFNModePriority, 
				dabnPlus1TARefFaultPriority, dabnPlus1TAMutePriority, dabnPlus1TAWarningTimeStampPriority, dabnPlus1TBRFPresentPriority, dabnPlus1TBInput1OKPriority, 
				dabnPlus1TBInput2OKPriority, dabnPlus1TBLocalModePriority, dabnPlus1TBFaultPriority, dabnPlus1TBWarningPriority, dabnPlus1TBInputPreselectionPriority, 
				dabnPlus1TBInputAutomaticPriority, dabnPlus1TBActiveInputPriority, dabnPlus1TBSFNModePriority, dabnPlus1TBRefFaultPriority, dabnPlus1TBMutePriority, 
				dabnPlus1TBWarningTimeStampPriority, dabnPlus1MTOpMode, dabnPlus1MTOpModeEnable, dabnPlus1MTOpModePriority }
			STATUS current
			DESCRIPTION 
				"Description.N+1 reserve: object group "
			::= { groupsnPlus1 1 }

		
		-- 1.3.6.1.4.1.19831.1.1.2.5.8.2
		eventGroupnPlus1 NOTIFICATION-GROUP
			NOTIFICATIONS { dabnPlus1RedundancySwitchOverEvent, dabnPlus1LocalModeEvent, dabnPlus1ControlUnitFaultEvent, dabnPlus1SwitchOverModeEvent, dabnPlus1SwitchOverReadyEvent, 
				dabnPlus1SwitchOverExecutedEvent, dabnPlus1SwitchOverFaultEvent, dabnPlus1ChannelSelectionEvent, dabnPlus1MTInputPreselectionEvent, dabnPlus1MTInputAutomaticEvent, 
				dabnPlus1MTRFProgramPresentEvent, dabnPlus1RTInputPreselectionEvent, dabnPlus1RTInputAutomaticEvent, dabnPlus1RTOpModeEvent, dabnPlus1RTRFProgramPresentEvent, 
				dabnPlus1TARFPresentEvent, dabnPlus1TAInput1OKEvent, dabnPlus1TAInput2OKEvent, dabnPlus1TALocalModeEvent, dabnPlus1TAInputPreselectionEvent, 
				dabnPlus1TAInputAutomaticEvent, dabnPlus1TAFaultEvent, dabnPlus1TAWarningEvent, dabnPlus1TAActiveInputEvent, dabnPlus1TASFNModeEvent, 
				dabnPlus1TARefFaultEvent, dabnPlus1TAMuteEvent, dabnPlus1TAWarningTimeStampEvent, dabnPlus1TBRFPresentEvent, dabnPlus1TBInput1OKEvent, 
				dabnPlus1TBInput2OKEvent, dabnPlus1TBLocalModeEvent, dabnPlus1TBFaultEvent, dabnPlus1TBWarningEvent, dabnPlus1TBInputPreselectionEvent, 
				dabnPlus1TBInputAutomaticEvent, dabnPlus1TBActiveInputEvent, dabnPlus1TBSFNModeEvent, dabnPlus1TBRefFaultEvent, dabnPlus1TBMuteEvent, 
				dabnPlus1TBWarningTimeStampEvent, dabnPlus1MTOpModeEvent }
			STATUS current
			DESCRIPTION 
				"Description.N+1 reserve:  group evets"
			::= { groupsnPlus1 2 }

		
		-- 1.3.6.1.4.1.19831.1.1.2.5.8.3
		objectGroupnPlus1obsolete OBJECT-GROUP
			OBJECTS { dabnPlus1ResetFault, dabnPlus1ResetFaultEnable, dabnPlus1ResetFaultPriority, dabnPlus1TransmitterBReset, dabnPlus1TransmitterBMode, 
				dabnPlus1TransmitterBResetEnable, dabnPlus1TransmitterBModeEnable, dabnPlus1TransmitterBResetPriority, dabnPlus1TransmitterBModePriority }
			STATUS obsolete
			DESCRIPTION 
				"Description.Inactive objects"
			::= { groupsnPlus1 3 }

		
		-- 1.3.6.1.4.1.19831.1.1.2.5.8.4
		eventGroupnPlus1obsolete NOTIFICATION-GROUP
			NOTIFICATIONS { dabnPlus1ResetFaultEvent, dabnPlus1TransmitterBResetEvent, dabnPlus1TransmitterBModeEvent }
			STATUS obsolete
			DESCRIPTION 
				"Description. Inactive notifications"
			::= { groupsnPlus1 4 }

		
		-- 1.3.6.1.4.1.19831.1.1.2.5.9
		compliancenPlus1 OBJECT IDENTIFIER ::= { dabnPlus1 9 }

		
		-- 1.3.6.1.4.1.19831.1.1.2.5.9.1
		dabnPlus1Compliance MODULE-COMPLIANCE
			STATUS current
			DESCRIPTION 
				"Compliance Statement"
			MODULE -- this module
				MANDATORY-GROUPS { objectGroupnPlus1, eventGroupnPlus1 }
			::= { compliancenPlus1 1 }

		
	
	END

--
-- IRT-DAB-NPLUS1-MIB.my
--
